; Geometric facade repair: genuine LINE and ARC architecture; source-traced planting.
; APPLOAD, then FACADE2. Data is embedded; estimated millimetres.
(setq F2:DATA '(
((0 . "LINE") (100 . "AcDbEntity") (8 . "GROUND") (62 . 7) (370 . 13) (100 . "AcDbLine") (10 0.0 0.0 0.0) (11
610.8597285068 0.0 0.0))
((0 . "LINE") (100 . "AcDbEntity") (8 . "GROUND") (62 . 7) (370 . 13) (100 . "AcDbLine") (10 610.8597285068 0.0 0.0) (11
2782.8054298643 0.0 0.0))
((0 . "LINE") (100 . "AcDbEntity") (8 . "GROUND") (62 . 7) (370 . 13) (100 . "AcDbLine") (10 2782.8054298643 0.0 0.0)
(11 2816.742081448 0.0 0.0))
((0 . "LINE") (100 . "AcDbEntity") (8 . "GROUND") (62 . 7) (370 . 13) (100 . "AcDbLine") (10 2816.742081448 0.0 0.0) (11
7873.3031674208 0.0 0.0))
((0 . "LINE") (100 . "AcDbEntity") (8 . "GROUND") (62 . 7) (370 . 13) (100 . "AcDbLine") (10 7873.3031674208 0.0 0.0)
(11 7929.8642533937 0.0 0.0))
((0 . "LINE") (100 . "AcDbEntity") (8 . "ARCH") (62 . 7) (370 . 13) (100 . "AcDbLine") (10 7929.8642533937 0.0 0.0) (11
9547.5113122172 0.0 0.0))
((0 . "LINE") (100 . "AcDbEntity") (8 . "ARCH") (62 . 7) (370 . 13) (100 . "AcDbLine") (10 9547.5113122172 0.0 0.0) (11
10452.4886877828 0.0 0.0))
((0 . "LINE") (100 . "AcDbEntity") (8 . "ARCH") (62 . 7) (370 . 13) (100 . "AcDbLine") (10 10452.4886877828 0.0 0.0) (11
12036.1990950226 0.0 0.0))
((0 . "LINE") (100 . "AcDbEntity") (8 . "GROUND") (62 . 7) (370 . 13) (100 . "AcDbLine") (10 12036.1990950226 0.0 0.0)
(11 12115.3846153846 0.0 0.0))
((0 . "LINE") (100 . "AcDbEntity") (8 . "GROUND") (62 . 7) (370 . 13) (100 . "AcDbLine") (10 12115.3846153846 0.0 0.0)
(11 17183.257918552 0.0 0.0))
((0 . "LINE") (100 . "AcDbEntity") (8 . "GROUND") (62 . 7) (370 . 13) (100 . "AcDbLine") (10 17183.257918552 0.0 0.0)
(11 17239.8190045249 0.0 0.0))
((0 . "LINE") (100 . "AcDbEntity") (8 . "GROUND") (62 . 7) (370 . 13) (100 . "AcDbLine") (10 17239.8190045249 0.0 0.0)
(11 19423.0769230769 0.0 0.0))
((0 . "LINE") (100 . "AcDbEntity") (8 . "GROUND") (62 . 7) (370 . 13) (100 . "AcDbLine") (10 19423.0769230769 0.0 0.0)
(11 19988.6877828054 0.0 0.0))
((0 . "LINE") (100 . "AcDbEntity") (8 . "ARCH") (62 . 7) (370 . 13) (100 . "AcDbLine") (10 610.8597285068 180.9954751131
0.0) (11 644.7963800905 180.9954751131 0.0))
((0 . "LINE") (100 . "AcDbEntity") (8 . "ARCH") (62 . 7) (370 . 13) (100 . "AcDbLine") (10 644.7963800905 180.9954751131
0.0) (11 892.175260181 180.9954751131 0.0))
((0 . "LINE") (100 . "AcDbEntity") (8 . "ARCH") (62 . 7) (370 . 13) (100 . "AcDbLine") (10 1030.9016628959
180.9954751131 0.0) (11 2782.8054298643 180.9954751131 0.0))
((0 . "LINE") (100 . "AcDbEntity") (8 . "ARCH") (62 . 7) (370 . 13) (100 . "AcDbLine") (10 2782.8054298643
180.9954751131 0.0) (11 2782.8054298643 0.0 0.0))
((0 . "LINE") (100 . "AcDbEntity") (8 . "ARCH") (62 . 7) (370 . 13) (100 . "AcDbLine") (10 610.8597285068 0.0 0.0) (11
610.8597285068 180.9954751131 0.0))
((0 . "LINE") (100 . "AcDbEntity") (8 . "ARCH") (62 . 7) (370 . 13) (100 . "AcDbLine") (10 17239.8190045249
180.9954751131 0.0) (11 17509.8223190045 180.9954751131 0.0))
((0 . "LINE") (100 . "AcDbEntity") (8 . "ARCH") (62 . 7) (370 . 13) (100 . "AcDbLine") (10 17648.5487217195
180.9954751131 0.0) (11 19389.1402714932 180.9954751131 0.0))
((0 . "LINE") (100 . "AcDbEntity") (8 . "ARCH") (62 . 7) (370 . 13) (100 . "AcDbLine") (10 19389.1402714932
180.9954751131 0.0) (11 19423.0769230769 180.9954751131 0.0))
((0 . "LINE") (100 . "AcDbEntity") (8 . "ARCH") (62 . 7) (370 . 13) (100 . "AcDbLine") (10 19423.0769230769
180.9954751131 0.0) (11 19423.0769230769 0.0 0.0))
((0 . "LINE") (100 . "AcDbEntity") (8 . "ARCH") (62 . 7) (370 . 13) (100 . "AcDbLine") (10 17239.8190045249 0.0 0.0) (11
17239.8190045249 180.9954751131 0.0))
((0 . "LINE") (100 . "AcDbEntity") (8 . "ARCH") (62 . 7) (370 . 13) (100 . "AcDbLine") (10 2816.742081448 214.9321266968
0.0) (11 7873.3031674208 214.9321266968 0.0))
((0 . "LINE") (100 . "AcDbEntity") (8 . "ARCH") (62 . 7) (370 . 13) (100 . "AcDbLine") (10 7873.3031674208
214.9321266968 0.0) (11 7873.3031674208 158.371040724 0.0))
((0 . "LINE") (100 . "AcDbEntity") (8 . "ARCH") (62 . 7) (370 . 13) (100 . "AcDbLine") (10 7873.3031674208 158.371040724
0.0) (11 7873.3031674208 0.0 0.0))
((0 . "LINE") (100 . "AcDbEntity") (8 . "ARCH") (62 . 7) (370 . 13) (100 . "AcDbLine") (10 2816.742081448 0.0 0.0) (11
2816.742081448 158.371040724 0.0))
((0 . "LINE") (100 . "AcDbEntity") (8 . "ARCH") (62 . 7) (370 . 13) (100 . "AcDbLine") (10 2816.742081448 158.371040724
0.0) (11 2816.742081448 214.9321266968 0.0))
((0 . "LINE") (100 . "AcDbEntity") (8 . "ARCH") (62 . 7) (370 . 13) (100 . "AcDbLine") (10 2816.742081448 158.371040724
0.0) (11 7873.3031674208 158.371040724 0.0))
((0 . "LINE") (100 . "AcDbEntity") (8 . "ARCH") (62 . 7) (370 . 13) (100 . "AcDbLine") (10 12115.3846153846
214.9321266968 0.0) (11 17183.257918552 214.9321266968 0.0))
((0 . "LINE") (100 . "AcDbEntity") (8 . "ARCH") (62 . 7) (370 . 13) (100 . "AcDbLine") (10 17183.257918552
214.9321266968 0.0) (11 17183.257918552 158.371040724 0.0))
((0 . "LINE") (100 . "AcDbEntity") (8 . "ARCH") (62 . 7) (370 . 13) (100 . "AcDbLine") (10 17183.257918552 158.371040724
0.0) (11 17183.257918552 0.0 0.0))
((0 . "LINE") (100 . "AcDbEntity") (8 . "ARCH") (62 . 7) (370 . 13) (100 . "AcDbLine") (10 12115.3846153846 0.0 0.0) (11
12115.3846153846 158.371040724 0.0))
((0 . "LINE") (100 . "AcDbEntity") (8 . "ARCH") (62 . 7) (370 . 13) (100 . "AcDbLine") (10 12115.3846153846
158.371040724 0.0) (11 12115.3846153846 214.9321266968 0.0))
((0 . "LINE") (100 . "AcDbEntity") (8 . "ARCH") (62 . 7) (370 . 13) (100 . "AcDbLine") (10 12115.3846153846
158.371040724 0.0) (11 17183.257918552 158.371040724 0.0))
((0 . "LINE") (100 . "AcDbEntity") (8 . "ARCH") (62 . 7) (370 . 13) (100 . "AcDbLine") (10 644.7963800905
5622.1719457014 0.0) (11 644.7963800905 5599.5475113122 0.0))
((0 . "LINE") (100 . "AcDbEntity") (8 . "ARCH") (62 . 7) (370 . 13) (100 . "AcDbLine") (10 644.7963800905
5599.5475113122 0.0) (11 644.7963800905 4819.0045248869 0.0))
((0 . "LINE") (100 . "AcDbEntity") (8 . "ARCH") (62 . 7) (370 . 13) (100 . "AcDbLine") (10 644.7963800905
4819.0045248869 0.0) (11 644.7963800905 4457.0135746606 0.0))
((0 . "LINE") (100 . "AcDbEntity") (8 . "ARCH") (62 . 7) (370 . 13) (100 . "AcDbLine") (10 644.7963800905
4457.0135746606 0.0) (11 644.7963800905 3834.8416289593 0.0))
((0 . "LINE") (100 . "AcDbEntity") (8 . "ARCH") (62 . 7) (370 . 13) (100 . "AcDbLine") (10 644.7963800905
3834.8416289593 0.0) (11 644.7963800905 2997.7375565611 0.0))
((0 . "LINE") (100 . "AcDbEntity") (8 . "ARCH") (62 . 7) (370 . 13) (100 . "AcDbLine") (10 644.7963800905
2805.4298642534 0.0) (11 644.7963800905 2047.5113122172 0.0))
((0 . "LINE") (100 . "AcDbEntity") (8 . "ARCH") (62 . 7) (370 . 13) (100 . "AcDbLine") (10 644.7963800905
2047.5113122172 0.0) (11 644.7963800905 1651.5837104072 0.0))
((0 . "LINE") (100 . "AcDbEntity") (8 . "ARCH") (62 . 7) (370 . 13) (100 . "AcDbLine") (10 644.7963800905
1651.5837104072 0.0) (11 644.7963800905 1006.7873303167 0.0))
((0 . "LINE") (100 . "AcDbEntity") (8 . "ARCH") (62 . 7) (370 . 13) (100 . "AcDbLine") (10 644.7963800905
1006.7873303167 0.0) (11 644.7963800905 180.9954751131 0.0))
((0 . "LINE") (100 . "AcDbEntity") (8 . "ARCH") (62 . 7) (370 . 13) (100 . "AcDbLine") (10 2782.8054298643
5622.1719457014 0.0) (11 2782.8054298643 5610.8597285068 0.0))
((0 . "LINE") (100 . "AcDbEntity") (8 . "ARCH") (62 . 7) (370 . 13) (100 . "AcDbLine") (10 2782.8054298643
5610.8597285068 0.0) (11 2782.8054298643 5599.5475113122 0.0))
((0 . "LINE") (100 . "AcDbEntity") (8 . "ARCH") (62 . 7) (370 . 13) (100 . "AcDbLine") (10 2782.8054298643
5599.5475113122 0.0) (11 2782.8054298643 4819.0045248869 0.0))
((0 . "LINE") (100 . "AcDbEntity") (8 . "ARCH") (62 . 7) (370 . 13) (100 . "AcDbLine") (10 2782.8054298643
4819.0045248869 0.0) (11 2782.8054298643 4457.0135746606 0.0))
((0 . "LINE") (100 . "AcDbEntity") (8 . "ARCH") (62 . 7) (370 . 13) (100 . "AcDbLine") (10 2782.8054298643
4457.0135746606 0.0) (11 2782.8054298643 3970.5882352941 0.0))
((0 . "LINE") (100 . "AcDbEntity") (8 . "ARCH") (62 . 7) (370 . 13) (100 . "AcDbLine") (10 2782.8054298643
2805.4298642534 0.0) (11 2782.8054298643 2047.5113122172 0.0))
((0 . "LINE") (100 . "AcDbEntity") (8 . "ARCH") (62 . 7) (370 . 13) (100 . "AcDbLine") (10 2782.8054298643
2047.5113122172 0.0) (11 2782.8054298643 1651.5837104072 0.0))
((0 . "LINE") (100 . "AcDbEntity") (8 . "ARCH") (62 . 7) (370 . 13) (100 . "AcDbLine") (10 2782.8054298643
1651.5837104072 0.0) (11 2782.8054298643 1142.5339366516 0.0))
((0 . "LINE") (100 . "AcDbEntity") (8 . "ARCH") (62 . 7) (370 . 13) (100 . "AcDbLine") (10 2782.8054298643
916.2895927602 0.0) (11 2782.8054298643 226.2443438914 0.0))
((0 . "LINE") (100 . "AcDbEntity") (8 . "ARCH") (62 . 7) (370 . 13) (100 . "AcDbLine") (10 2782.8054298643
226.2443438914 0.0) (11 2782.8054298643 180.9954751131 0.0))
((0 . "LINE") (100 . "AcDbEntity") (8 . "ARCH") (62 . 7) (370 . 13) (100 . "AcDbLine") (10 610.8597285068
2997.7375565611 0.0) (11 644.7963800905 2997.7375565611 0.0))
((0 . "LINE") (100 . "AcDbEntity") (8 . "ARCH") (62 . 7) (370 . 13) (100 . "AcDbLine") (10 644.7963800905
2997.7375565611 0.0) (11 894.9343325792 2997.7375565611 0.0))
((0 . "LINE") (100 . "AcDbEntity") (8 . "ARCH") (62 . 7) (370 . 13) (100 . "AcDbLine") (10 1028.1425904977
2997.7375565611 0.0) (11 2782.8054298643 2997.7375565611 0.0))
((0 . "LINE") (100 . "AcDbEntity") (8 . "ARCH") (62 . 7) (370 . 13) (100 . "AcDbLine") (10 2782.8054298643
2997.7375565611 0.0) (11 2782.8054298643 2861.9909502262 0.0))
((0 . "LINE") (100 . "AcDbEntity") (8 . "ARCH") (62 . 7) (370 . 13) (100 . "AcDbLine") (10 2782.8054298643
2861.9909502262 0.0) (11 2782.8054298643 2805.4298642534 0.0))
((0 . "LINE") (100 . "AcDbEntity") (8 . "ARCH") (62 . 7) (370 . 13) (100 . "AcDbLine") (10 2782.8054298643
2805.4298642534 0.0) (11 644.7963800905 2805.4298642534 0.0))
((0 . "LINE") (100 . "AcDbEntity") (8 . "ARCH") (62 . 7) (370 . 13) (100 . "AcDbLine") (10 644.7963800905
2805.4298642534 0.0) (11 610.8597285068 2805.4298642534 0.0))
((0 . "LINE") (100 . "AcDbEntity") (8 . "ARCH") (62 . 7) (370 . 13) (100 . "AcDbLine") (10 610.8597285068
2805.4298642534 0.0) (11 610.8597285068 2861.9909502262 0.0))
((0 . "LINE") (100 . "AcDbEntity") (8 . "ARCH") (62 . 7) (370 . 13) (100 . "AcDbLine") (10 610.8597285068
2861.9909502262 0.0) (11 610.8597285068 2997.7375565611 0.0))
((0 . "LINE") (100 . "AcDbEntity") (8 . "ARCH") (62 . 7) (370 . 13) (100 . "AcDbLine") (10 610.8597285068
2861.9909502262 0.0) (11 2782.8054298643 2861.9909502262 0.0))
((0 . "LINE") (100 . "AcDbEntity") (8 . "ARCH") (62 . 7) (370 . 13) (100 . "AcDbLine") (10 644.7963800905
4819.0045248869 0.0) (11 1018.0995475113 4819.0045248869 0.0))
((0 . "LINE") (100 . "AcDbEntity") (8 . "ARCH") (62 . 7) (370 . 13) (100 . "AcDbLine") (10 2680.9954751131
4819.0045248869 0.0) (11 2782.8054298643 4819.0045248869 0.0))
((0 . "LINE") (100 . "AcDbEntity") (8 . "ARCH") (62 . 7) (370 . 13) (100 . "AcDbLine") (10 644.7963800905
4457.0135746606 0.0) (11 1018.0995475113 4457.0135746606 0.0))
((0 . "LINE") (100 . "AcDbEntity") (8 . "ARCH") (62 . 7) (370 . 13) (100 . "AcDbLine") (10 2680.9954751131
4457.0135746606 0.0) (11 2782.8054298643 4457.0135746606 0.0))
((0 . "LINE") (100 . "AcDbEntity") (8 . "ARCH") (62 . 7) (370 . 13) (100 . "AcDbLine") (10 644.7963800905
2047.5113122172 0.0) (11 1018.0995475113 2047.5113122172 0.0))
((0 . "LINE") (100 . "AcDbEntity") (8 . "ARCH") (62 . 7) (370 . 13) (100 . "AcDbLine") (10 2680.9954751131
2047.5113122172 0.0) (11 2782.8054298643 2047.5113122172 0.0))
((0 . "LINE") (100 . "AcDbEntity") (8 . "ARCH") (62 . 7) (370 . 13) (100 . "AcDbLine") (10 644.7963800905
1651.5837104072 0.0) (11 1018.0995475113 1651.5837104072 0.0))
((0 . "LINE") (100 . "AcDbEntity") (8 . "ARCH") (62 . 7) (370 . 13) (100 . "AcDbLine") (10 2680.9954751131
1651.5837104072 0.0) (11 2782.8054298643 1651.5837104072 0.0))
((0 . "LINE") (100 . "AcDbEntity") (8 . "ARCH") (62 . 7) (370 . 13) (100 . "AcDbLine") (10 644.7963800905
5882.3529411765 0.0) (11 644.7963800905 5890.0783597285 0.0))
((0 . "LINE") (100 . "AcDbEntity") (8 . "ARCH") (62 . 7) (370 . 13) (100 . "AcDbLine") (10 644.7963800905
5890.0783597285 0.0) (11 644.7963800905 6481.9004524887 0.0))
((0 . "LINE") (100 . "AcDbEntity") (8 . "ARCH") (62 . 7) (370 . 13) (100 . "AcDbLine") (10 644.7963800905
6481.9004524887 0.0) (11 1606.334841629 6481.9004524887 0.0))
((0 . "LINE") (100 . "AcDbEntity") (8 . "ARCH") (62 . 7) (370 . 13) (100 . "AcDbLine") (10 1606.334841629
6481.9004524887 0.0) (11 1606.334841629 6334.8416289593 0.0))
((0 . "LINE") (100 . "AcDbEntity") (8 . "ARCH") (62 . 7) (370 . 13) (100 . "AcDbLine") (10 1606.334841629
6334.8416289593 0.0) (11 1889.1402714932 6334.8416289593 0.0))
((0 . "LINE") (100 . "AcDbEntity") (8 . "ARCH") (62 . 7) (370 . 13) (100 . "AcDbLine") (10 1889.1402714932
6334.8416289593 0.0) (11 1889.1402714932 6481.9004524887 0.0))
((0 . "LINE") (100 . "AcDbEntity") (8 . "ARCH") (62 . 7) (370 . 13) (100 . "AcDbLine") (10 1889.1402714932
6481.9004524887 0.0) (11 2726.2443438914 6481.9004524887 0.0))
((0 . "LINE") (100 . "AcDbEntity") (8 . "ARCH") (62 . 7) (370 . 13) (100 . "AcDbLine") (10 2726.2443438914
6481.9004524887 0.0) (11 2782.8054298643 6481.9004524887 0.0))
((0 . "LINE") (100 . "AcDbEntity") (8 . "ARCH") (62 . 7) (370 . 13) (100 . "AcDbLine") (10 622.1719457014
6481.9004524887 0.0) (11 622.1719457014 6549.7737556561 0.0))
((0 . "LINE") (100 . "AcDbEntity") (8 . "ARCH") (62 . 7) (370 . 13) (100 . "AcDbLine") (10 622.1719457014
6549.7737556561 0.0) (11 1674.2081447964 6549.7737556561 0.0))
((0 . "LINE") (100 . "AcDbEntity") (8 . "ARCH") (62 . 7) (370 . 13) (100 . "AcDbLine") (10 1674.2081447964
6549.7737556561 0.0) (11 1674.2081447964 6391.4027149321 0.0))
((0 . "LINE") (100 . "AcDbEntity") (8 . "ARCH") (62 . 7) (370 . 13) (100 . "AcDbLine") (10 1674.2081447964
6391.4027149321 0.0) (11 1832.5791855204 6391.4027149321 0.0))
((0 . "LINE") (100 . "AcDbEntity") (8 . "ARCH") (62 . 7) (370 . 13) (100 . "AcDbLine") (10 1832.5791855204
6391.4027149321 0.0) (11 1832.5791855204 6549.7737556561 0.0))
((0 . "LINE") (100 . "AcDbEntity") (8 . "ARCH") (62 . 7) (370 . 13) (100 . "AcDbLine") (10 1832.5791855204
6549.7737556561 0.0) (11 2726.2443438914 6549.7737556561 0.0))
((0 . "LINE") (100 . "AcDbEntity") (8 . "ARCH") (62 . 7) (370 . 13) (100 . "AcDbLine") (10 2726.2443438914
6549.7737556561 0.0) (11 2782.8054298643 6549.7737556561 0.0))
((0 . "LINE") (100 . "AcDbEntity") (8 . "ARCH") (62 . 7) (370 . 13) (100 . "AcDbLine") (10 441.1764705882
5803.1674208145 0.0) (11 644.7963800905 5890.0783597285 0.0))
((0 . "LINE") (100 . "AcDbEntity") (8 . "ARCH") (62 . 7) (370 . 13) (100 . "AcDbLine") (10 644.7963800905
5890.0783597285 0.0) (11 1368.778280543 6199.0950226244 0.0))
((0 . "LINE") (100 . "AcDbEntity") (8 . "ARCH") (62 . 7) (370 . 13) (100 . "AcDbLine") (10 1368.778280543
6199.0950226244 0.0) (11 2782.8054298643 6199.0950226244 0.0))
((0 . "LINE") (100 . "AcDbEntity") (8 . "ARCH") (62 . 7) (370 . 13) (100 . "AcDbLine") (10 441.1764705882
5803.1674208145 0.0) (11 441.1764705882 5757.9185520362 0.0))
((0 . "LINE") (100 . "AcDbEntity") (8 . "ARCH") (62 . 7) (370 . 13) (100 . "AcDbLine") (10 441.1764705882
5757.9185520362 0.0) (11 466.628959276 5746.6063348416 0.0))
((0 . "LINE") (100 . "AcDbEntity") (8 . "ARCH") (62 . 7) (370 . 13) (100 . "AcDbLine") (10 466.628959276 5746.6063348416
0.0) (11 542.9864253394 5712.6696832579 0.0))
((0 . "LINE") (100 . "AcDbEntity") (8 . "ARCH") (62 . 7) (370 . 13) (100 . "AcDbLine") (10 542.9864253394
5712.6696832579 0.0) (11 542.9864253394 5667.4208144796 0.0))
((0 . "LINE") (100 . "AcDbEntity") (8 . "ARCH") (62 . 7) (370 . 13) (100 . "AcDbLine") (10 542.9864253394
5667.4208144796 0.0) (11 588.2352941176 5667.4208144796 0.0))
((0 . "LINE") (100 . "AcDbEntity") (8 . "ARCH") (62 . 7) (370 . 13) (100 . "AcDbLine") (10 588.2352941176
5667.4208144796 0.0) (11 588.2352941176 5599.5475113122 0.0))
((0 . "LINE") (100 . "AcDbEntity") (8 . "ARCH") (62 . 7) (370 . 13) (100 . "AcDbLine") (10 588.2352941176
5599.5475113122 0.0) (11 644.7963800905 5599.5475113122 0.0))
((0 . "LINE") (100 . "AcDbEntity") (8 . "ARCH") (62 . 7) (370 . 13) (100 . "AcDbLine") (10 644.7963800905
5599.5475113122 0.0) (11 2782.8054298643 5599.5475113122 0.0))
((0 . "LINE") (100 . "AcDbEntity") (8 . "ARCH") (62 . 7) (370 . 13) (100 . "AcDbLine") (10 441.1764705882
5803.1674208145 0.0) (11 2782.8054298643 5803.1674208145 0.0))
((0 . "LINE") (100 . "AcDbEntity") (8 . "ARCH") (62 . 7) (370 . 13) (100 . "AcDbLine") (10 466.628959276 5746.6063348416
0.0) (11 2782.8054298643 5746.6063348416 0.0))
((0 . "LINE") (100 . "AcDbEntity") (8 . "ARCH") (62 . 7) (370 . 13) (100 . "AcDbLine") (10 588.2352941176
5667.4208144796 0.0) (11 2782.8054298643 5667.4208144796 0.0))
((0 . "LINE") (100 . "AcDbEntity") (8 . "ARCH") (62 . 7) (370 . 13) (100 . "AcDbLine") (10 17239.8190045249
5622.1719457014 0.0) (11 17239.8190045249 5610.8597285068 0.0))
((0 . "LINE") (100 . "AcDbEntity") (8 . "ARCH") (62 . 7) (370 . 13) (100 . "AcDbLine") (10 17239.8190045249
5610.8597285068 0.0) (11 17239.8190045249 5599.5475113122 0.0))
((0 . "LINE") (100 . "AcDbEntity") (8 . "ARCH") (62 . 7) (370 . 13) (100 . "AcDbLine") (10 17239.8190045249
5599.5475113122 0.0) (11 17239.8190045249 4819.0045248869 0.0))
((0 . "LINE") (100 . "AcDbEntity") (8 . "ARCH") (62 . 7) (370 . 13) (100 . "AcDbLine") (10 17239.8190045249
4819.0045248869 0.0) (11 17239.8190045249 4457.0135746606 0.0))
((0 . "LINE") (100 . "AcDbEntity") (8 . "ARCH") (62 . 7) (370 . 13) (100 . "AcDbLine") (10 17239.8190045249
4457.0135746606 0.0) (11 17239.8190045249 3789.592760181 0.0))
((0 . "LINE") (100 . "AcDbEntity") (8 . "ARCH") (62 . 7) (370 . 13) (100 . "AcDbLine") (10 17239.8190045249
3789.592760181 0.0) (11 17239.8190045249 3721.7194570136 0.0))
((0 . "LINE") (100 . "AcDbEntity") (8 . "ARCH") (62 . 7) (370 . 13) (100 . "AcDbLine") (10 17239.8190045249
3721.7194570136 0.0) (11 17239.8190045249 3597.2850678733 0.0))
((0 . "LINE") (100 . "AcDbEntity") (8 . "ARCH") (62 . 7) (370 . 13) (100 . "AcDbLine") (10 17239.8190045249
3597.2850678733 0.0) (11 17239.8190045249 3585.9728506787 0.0))
((0 . "LINE") (100 . "AcDbEntity") (8 . "ARCH") (62 . 7) (370 . 13) (100 . "AcDbLine") (10 17239.8190045249
3585.9728506787 0.0) (11 17239.8190045249 2997.7375565611 0.0))
((0 . "LINE") (100 . "AcDbEntity") (8 . "ARCH") (62 . 7) (370 . 13) (100 . "AcDbLine") (10 17239.8190045249
2805.4298642534 0.0) (11 17239.8190045249 2047.5113122172 0.0))
((0 . "LINE") (100 . "AcDbEntity") (8 . "ARCH") (62 . 7) (370 . 13) (100 . "AcDbLine") (10 17239.8190045249
2047.5113122172 0.0) (11 17239.8190045249 1651.5837104072 0.0))
((0 . "LINE") (100 . "AcDbEntity") (8 . "ARCH") (62 . 7) (370 . 13) (100 . "AcDbLine") (10 17239.8190045249
1651.5837104072 0.0) (11 17239.8190045249 180.9954751131 0.0))
((0 . "LINE") (100 . "AcDbEntity") (8 . "ARCH") (62 . 7) (370 . 13) (100 . "AcDbLine") (10 19389.1402714932
5622.1719457014 0.0) (11 19389.1402714932 5599.5475113122 0.0))
((0 . "LINE") (100 . "AcDbEntity") (8 . "ARCH") (62 . 7) (370 . 13) (100 . "AcDbLine") (10 19389.1402714932
5599.5475113122 0.0) (11 19389.1402714932 4819.0045248869 0.0))
((0 . "LINE") (100 . "AcDbEntity") (8 . "ARCH") (62 . 7) (370 . 13) (100 . "AcDbLine") (10 19389.1402714932
4819.0045248869 0.0) (11 19389.1402714932 4457.0135746606 0.0))
((0 . "LINE") (100 . "AcDbEntity") (8 . "ARCH") (62 . 7) (370 . 13) (100 . "AcDbLine") (10 19389.1402714932
4457.0135746606 0.0) (11 19389.1402714932 3984.5109615385 0.0))
((0 . "LINE") (100 . "AcDbEntity") (8 . "ARCH") (62 . 7) (370 . 13) (100 . "AcDbLine") (10 19389.1402714932
2805.4298642534 0.0) (11 19389.1402714932 2047.5113122172 0.0))
((0 . "LINE") (100 . "AcDbEntity") (8 . "ARCH") (62 . 7) (370 . 13) (100 . "AcDbLine") (10 19389.1402714932
2047.5113122172 0.0) (11 19389.1402714932 1651.5837104072 0.0))
((0 . "LINE") (100 . "AcDbEntity") (8 . "ARCH") (62 . 7) (370 . 13) (100 . "AcDbLine") (10 19389.1402714932
1651.5837104072 0.0) (11 19389.1402714932 1156.4566628959 0.0))
((0 . "LINE") (100 . "AcDbEntity") (8 . "ARCH") (62 . 7) (370 . 13) (100 . "AcDbLine") (10 19389.1402714932
916.2895927602 0.0) (11 19389.1402714932 180.9954751131 0.0))
((0 . "LINE") (100 . "AcDbEntity") (8 . "ARCH") (62 . 7) (370 . 13) (100 . "AcDbLine") (10 17205.8823529412
2997.7375565611 0.0) (11 17239.8190045249 2997.7375565611 0.0))
((0 . "LINE") (100 . "AcDbEntity") (8 . "ARCH") (62 . 7) (370 . 13) (100 . "AcDbLine") (10 17239.8190045249
2997.7375565611 0.0) (11 17512.5813914027 2997.7375565611 0.0))
((0 . "LINE") (100 . "AcDbEntity") (8 . "ARCH") (62 . 7) (370 . 13) (100 . "AcDbLine") (10 17645.7896493213
2997.7375565611 0.0) (11 19028.7653506787 2997.7375565611 0.0))
((0 . "LINE") (100 . "AcDbEntity") (8 . "ARCH") (62 . 7) (370 . 13) (100 . "AcDbLine") (10 19149.9960294118
2997.7375565611 0.0) (11 19389.1402714932 2997.7375565611 0.0))
((0 . "LINE") (100 . "AcDbEntity") (8 . "ARCH") (62 . 7) (370 . 13) (100 . "AcDbLine") (10 19389.1402714932
2997.7375565611 0.0) (11 19389.1402714932 2861.9909502262 0.0))
((0 . "LINE") (100 . "AcDbEntity") (8 . "ARCH") (62 . 7) (370 . 13) (100 . "AcDbLine") (10 19389.1402714932
2861.9909502262 0.0) (11 19389.1402714932 2805.4298642534 0.0))
((0 . "LINE") (100 . "AcDbEntity") (8 . "ARCH") (62 . 7) (370 . 13) (100 . "AcDbLine") (10 19389.1402714932
2805.4298642534 0.0) (11 19112.8840158371 2805.4298642534 0.0))
((0 . "LINE") (100 . "AcDbEntity") (8 . "ARCH") (62 . 7) (370 . 13) (100 . "AcDbLine") (10 19094.6994230769
2805.4298642534 0.0) (11 17239.8190045249 2805.4298642534 0.0))
((0 . "LINE") (100 . "AcDbEntity") (8 . "ARCH") (62 . 7) (370 . 13) (100 . "AcDbLine") (10 17239.8190045249
2805.4298642534 0.0) (11 17205.8823529412 2805.4298642534 0.0))
((0 . "LINE") (100 . "AcDbEntity") (8 . "ARCH") (62 . 7) (370 . 13) (100 . "AcDbLine") (10 17205.8823529412
2805.4298642534 0.0) (11 17205.8823529412 2861.9909502262 0.0))
((0 . "LINE") (100 . "AcDbEntity") (8 . "ARCH") (62 . 7) (370 . 13) (100 . "AcDbLine") (10 17205.8823529412
2861.9909502262 0.0) (11 17205.8823529412 2997.7375565611 0.0))
((0 . "LINE") (100 . "AcDbEntity") (8 . "ARCH") (62 . 7) (370 . 13) (100 . "AcDbLine") (10 17205.8823529412
2861.9909502262 0.0) (11 17239.8190045249 2861.9909502262 0.0))
((0 . "LINE") (100 . "AcDbEntity") (8 . "ARCH") (62 . 7) (370 . 13) (100 . "AcDbLine") (10 17239.8190045249
2861.9909502262 0.0) (11 19075.3070475113 2861.9909502262 0.0))
((0 . "LINE") (100 . "AcDbEntity") (8 . "ARCH") (62 . 7) (370 . 13) (100 . "AcDbLine") (10 19123.799321267
2861.9909502262 0.0) (11 19389.1402714932 2861.9909502262 0.0))
((0 . "LINE") (100 . "AcDbEntity") (8 . "ARCH") (62 . 7) (370 . 13) (100 . "AcDbLine") (10 17239.8190045249
4819.0045248869 0.0) (11 17352.9411764706 4819.0045248869 0.0))
((0 . "LINE") (100 . "AcDbEntity") (8 . "ARCH") (62 . 7) (370 . 13) (100 . "AcDbLine") (10 19015.8371040724
4819.0045248869 0.0) (11 19389.1402714932 4819.0045248869 0.0))
((0 . "LINE") (100 . "AcDbEntity") (8 . "ARCH") (62 . 7) (370 . 13) (100 . "AcDbLine") (10 17239.8190045249
4457.0135746606 0.0) (11 17352.9411764706 4457.0135746606 0.0))
((0 . "LINE") (100 . "AcDbEntity") (8 . "ARCH") (62 . 7) (370 . 13) (100 . "AcDbLine") (10 19015.8371040724
4457.0135746606 0.0) (11 19389.1402714932 4457.0135746606 0.0))
((0 . "LINE") (100 . "AcDbEntity") (8 . "ARCH") (62 . 7) (370 . 13) (100 . "AcDbLine") (10 17239.8190045249
2047.5113122172 0.0) (11 17352.9411764706 2047.5113122172 0.0))
((0 . "LINE") (100 . "AcDbEntity") (8 . "ARCH") (62 . 7) (370 . 13) (100 . "AcDbLine") (10 19015.8371040724
2047.5113122172 0.0) (11 19389.1402714932 2047.5113122172 0.0))
((0 . "LINE") (100 . "AcDbEntity") (8 . "ARCH") (62 . 7) (370 . 13) (100 . "AcDbLine") (10 17239.8190045249
1651.5837104072 0.0) (11 17352.9411764706 1651.5837104072 0.0))
((0 . "LINE") (100 . "AcDbEntity") (8 . "ARCH") (62 . 7) (370 . 13) (100 . "AcDbLine") (10 19015.8371040724
1651.5837104072 0.0) (11 19389.1402714932 1651.5837104072 0.0))
((0 . "LINE") (100 . "AcDbEntity") (8 . "ARCH") (62 . 7) (370 . 13) (100 . "AcDbLine") (10 19389.1402714932
5871.0407239819 0.0) (11 19389.1402714932 5894.9067420814 0.0))
((0 . "LINE") (100 . "AcDbEntity") (8 . "ARCH") (62 . 7) (370 . 13) (100 . "AcDbLine") (10 19389.1402714932
5894.9067420814 0.0) (11 19389.1402714932 6481.9004524887 0.0))
((0 . "LINE") (100 . "AcDbEntity") (8 . "ARCH") (62 . 7) (370 . 13) (100 . "AcDbLine") (10 19389.1402714932
6481.9004524887 0.0) (11 18416.2895927602 6481.9004524887 0.0))
((0 . "LINE") (100 . "AcDbEntity") (8 . "ARCH") (62 . 7) (370 . 13) (100 . "AcDbLine") (10 18416.2895927602
6481.9004524887 0.0) (11 18416.2895927602 6334.8416289593 0.0))
((0 . "LINE") (100 . "AcDbEntity") (8 . "ARCH") (62 . 7) (370 . 13) (100 . "AcDbLine") (10 18416.2895927602
6334.8416289593 0.0) (11 18144.7963800905 6334.8416289593 0.0))
((0 . "LINE") (100 . "AcDbEntity") (8 . "ARCH") (62 . 7) (370 . 13) (100 . "AcDbLine") (10 18144.7963800905
6334.8416289593 0.0) (11 18144.7963800905 6481.9004524887 0.0))
((0 . "LINE") (100 . "AcDbEntity") (8 . "ARCH") (62 . 7) (370 . 13) (100 . "AcDbLine") (10 18144.7963800905
6481.9004524887 0.0) (11 17330.3167420814 6481.9004524887 0.0))
((0 . "LINE") (100 . "AcDbEntity") (8 . "ARCH") (62 . 7) (370 . 13) (100 . "AcDbLine") (10 17330.3167420814
6481.9004524887 0.0) (11 17239.8190045249 6481.9004524887 0.0))
((0 . "LINE") (100 . "AcDbEntity") (8 . "ARCH") (62 . 7) (370 . 13) (100 . "AcDbLine") (10 19423.0769230769
6481.9004524887 0.0) (11 19423.0769230769 6549.7737556561 0.0))
((0 . "LINE") (100 . "AcDbEntity") (8 . "ARCH") (62 . 7) (370 . 13) (100 . "AcDbLine") (10 19423.0769230769
6549.7737556561 0.0) (11 18371.0407239819 6549.7737556561 0.0))
((0 . "LINE") (100 . "AcDbEntity") (8 . "ARCH") (62 . 7) (370 . 13) (100 . "AcDbLine") (10 18371.0407239819
6549.7737556561 0.0) (11 18223.9819004525 6549.7737556561 0.0))
((0 . "LINE") (100 . "AcDbEntity") (8 . "ARCH") (62 . 7) (370 . 13) (100 . "AcDbLine") (10 18223.9819004525
6549.7737556561 0.0) (11 18223.9819004525 6391.4027149321 0.0))
((0 . "LINE") (100 . "AcDbEntity") (8 . "ARCH") (62 . 7) (370 . 13) (100 . "AcDbLine") (10 18223.9819004525
6391.4027149321 0.0) (11 18371.0407239819 6391.4027149321 0.0))
((0 . "LINE") (100 . "AcDbEntity") (8 . "ARCH") (62 . 7) (370 . 13) (100 . "AcDbLine") (10 18371.0407239819
6391.4027149321 0.0) (11 18371.0407239819 6549.7737556561 0.0))
((0 . "LINE") (100 . "AcDbEntity") (8 . "ARCH") (62 . 7) (370 . 13) (100 . "AcDbLine") (10 18223.9819004525
6549.7737556561 0.0) (11 17330.3167420814 6549.7737556561 0.0))
((0 . "LINE") (100 . "AcDbEntity") (8 . "ARCH") (62 . 7) (370 . 13) (100 . "AcDbLine") (10 17330.3167420814
6549.7737556561 0.0) (11 17239.8190045249 6549.7737556561 0.0))
((0 . "LINE") (100 . "AcDbEntity") (8 . "ARCH") (62 . 7) (370 . 13) (100 . "AcDbLine") (10 19604.07239819
5803.1674208145 0.0) (11 19389.1402714932 5894.9067420814 0.0))
((0 . "LINE") (100 . "AcDbEntity") (8 . "ARCH") (62 . 7) (370 . 13) (100 . "AcDbLine") (10 19389.1402714932
5894.9067420814 0.0) (11 18676.4705882353 6199.0950226244 0.0))
((0 . "LINE") (100 . "AcDbEntity") (8 . "ARCH") (62 . 7) (370 . 13) (100 . "AcDbLine") (10 18676.4705882353
6199.0950226244 0.0) (11 17239.8190045249 6199.0950226244 0.0))
((0 . "LINE") (100 . "AcDbEntity") (8 . "ARCH") (62 . 7) (370 . 13) (100 . "AcDbLine") (10 19604.07239819
5803.1674208145 0.0) (11 19604.07239819 5757.9185520362 0.0))
((0 . "LINE") (100 . "AcDbEntity") (8 . "ARCH") (62 . 7) (370 . 13) (100 . "AcDbLine") (10 19604.07239819
5757.9185520362 0.0) (11 19581.4479638009 5746.6063348416 0.0))
((0 . "LINE") (100 . "AcDbEntity") (8 . "ARCH") (62 . 7) (370 . 13) (100 . "AcDbLine") (10 19581.4479638009
5746.6063348416 0.0) (11 19513.5746606335 5712.6696832579 0.0))
((0 . "LINE") (100 . "AcDbEntity") (8 . "ARCH") (62 . 7) (370 . 13) (100 . "AcDbLine") (10 19513.5746606335
5712.6696832579 0.0) (11 19513.5746606335 5667.4208144796 0.0))
((0 . "LINE") (100 . "AcDbEntity") (8 . "ARCH") (62 . 7) (370 . 13) (100 . "AcDbLine") (10 19513.5746606335
5667.4208144796 0.0) (11 19468.3257918552 5667.4208144796 0.0))
((0 . "LINE") (100 . "AcDbEntity") (8 . "ARCH") (62 . 7) (370 . 13) (100 . "AcDbLine") (10 19468.3257918552
5667.4208144796 0.0) (11 19468.3257918552 5599.5475113122 0.0))
((0 . "LINE") (100 . "AcDbEntity") (8 . "ARCH") (62 . 7) (370 . 13) (100 . "AcDbLine") (10 19468.3257918552
5599.5475113122 0.0) (11 19389.1402714932 5599.5475113122 0.0))
((0 . "LINE") (100 . "AcDbEntity") (8 . "ARCH") (62 . 7) (370 . 13) (100 . "AcDbLine") (10 19389.1402714932
5599.5475113122 0.0) (11 17239.8190045249 5599.5475113122 0.0))
((0 . "LINE") (100 . "AcDbEntity") (8 . "ARCH") (62 . 7) (370 . 13) (100 . "AcDbLine") (10 17239.8190045249
5803.1674208145 0.0) (11 19604.07239819 5803.1674208145 0.0))
((0 . "LINE") (100 . "AcDbEntity") (8 . "ARCH") (62 . 7) (370 . 13) (100 . "AcDbLine") (10 17239.8190045249
5746.6063348416 0.0) (11 19581.4479638009 5746.6063348416 0.0))
((0 . "LINE") (100 . "AcDbEntity") (8 . "ARCH") (62 . 7) (370 . 13) (100 . "AcDbLine") (10 17239.8190045249
5667.4208144796 0.0) (11 19468.3257918552 5667.4208144796 0.0))
((0 . "LINE") (100 . "AcDbEntity") (8 . "ARCH") (62 . 7) (370 . 13) (100 . "AcDbLine") (10 2782.8054298643
6481.9004524887 0.0) (11 2782.8054298643 6199.0950226244 0.0))
((0 . "LINE") (100 . "AcDbEntity") (8 . "ARCH") (62 . 7) (370 . 13) (100 . "AcDbLine") (10 2782.8054298643
6199.0950226244 0.0) (11 2782.8054298643 5814.4796380091 0.0))
((0 . "LINE") (100 . "AcDbEntity") (8 . "ARCH") (62 . 7) (370 . 13) (100 . "AcDbLine") (10 2782.8054298643
5814.4796380091 0.0) (11 2782.8054298643 5803.1674208145 0.0))
((0 . "LINE") (100 . "AcDbEntity") (8 . "ARCH") (62 . 7) (370 . 13) (100 . "AcDbLine") (10 2782.8054298643
5803.1674208145 0.0) (11 2782.8054298643 5746.6063348416 0.0))
((0 . "LINE") (100 . "AcDbEntity") (8 . "ARCH") (62 . 7) (370 . 13) (100 . "AcDbLine") (10 2782.8054298643
5746.6063348416 0.0) (11 2782.8054298643 5667.4208144796 0.0))
((0 . "LINE") (100 . "AcDbEntity") (8 . "ARCH") (62 . 7) (370 . 13) (100 . "AcDbLine") (10 2782.8054298643
5667.4208144796 0.0) (11 2782.8054298643 5622.1719457014 0.0))
((0 . "LINE") (100 . "AcDbEntity") (8 . "ARCH") (62 . 7) (370 . 13) (100 . "AcDbLine") (10 7929.8642533937
6481.9004524887 0.0) (11 7929.8642533937 6470.5882352941 0.0))
((0 . "LINE") (100 . "AcDbEntity") (8 . "ARCH") (62 . 7) (370 . 13) (100 . "AcDbLine") (10 7929.8642533937
6470.5882352941 0.0) (11 7929.8642533937 6199.0950226244 0.0))
((0 . "LINE") (100 . "AcDbEntity") (8 . "ARCH") (62 . 7) (370 . 13) (100 . "AcDbLine") (10 7929.8642533937
6199.0950226244 0.0) (11 7929.8642533937 5814.4796380091 0.0))
((0 . "LINE") (100 . "AcDbEntity") (8 . "ARCH") (62 . 7) (370 . 13) (100 . "AcDbLine") (10 7929.8642533937
5814.4796380091 0.0) (11 7929.8642533937 5746.6063348416 0.0))
((0 . "LINE") (100 . "AcDbEntity") (8 . "ARCH") (62 . 7) (370 . 13) (100 . "AcDbLine") (10 7929.8642533937
5746.6063348416 0.0) (11 7929.8642533937 5735.2941176471 0.0))
((0 . "LINE") (100 . "AcDbEntity") (8 . "ARCH") (62 . 7) (370 . 13) (100 . "AcDbLine") (10 7929.8642533937
5735.2941176471 0.0) (11 7929.8642533937 5610.8597285068 0.0))
((0 . "LINE") (100 . "AcDbEntity") (8 . "ARCH") (62 . 7) (370 . 13) (100 . "AcDbLine") (10 7929.8642533937
5610.8597285068 0.0) (11 7929.8642533937 5599.5475113122 0.0))
((0 . "LINE") (100 . "AcDbEntity") (8 . "ARCH") (62 . 7) (370 . 13) (100 . "AcDbLine") (10 7929.8642533937
5599.5475113122 0.0) (11 7929.8642533937 4909.5022624434 0.0))
((0 . "LINE") (100 . "AcDbEntity") (8 . "ARCH") (62 . 7) (370 . 13) (100 . "AcDbLine") (10 7929.8642533937
4909.5022624434 0.0) (11 7929.8642533937 3789.592760181 0.0))
((0 . "LINE") (100 . "AcDbEntity") (8 . "ARCH") (62 . 7) (370 . 13) (100 . "AcDbLine") (10 2782.8054298643
3597.2850678733 0.0) (11 2782.8054298643 3585.9728506787 0.0))
((0 . "LINE") (100 . "AcDbEntity") (8 . "ARCH") (62 . 7) (370 . 13) (100 . "AcDbLine") (10 2782.8054298643
3585.9728506787 0.0) (11 2782.8054298643 2997.7375565611 0.0))
((0 . "LINE") (100 . "AcDbEntity") (8 . "ARCH") (62 . 7) (370 . 13) (100 . "AcDbLine") (10 7929.8642533937
3597.2850678733 0.0) (11 7929.8642533937 3585.9728506787 0.0))
((0 . "LINE") (100 . "AcDbEntity") (8 . "ARCH") (62 . 7) (370 . 13) (100 . "AcDbLine") (10 7929.8642533937
3585.9728506787 0.0) (11 7929.8642533937 2816.742081448 0.0))
((0 . "LINE") (100 . "AcDbEntity") (8 . "ARCH") (62 . 7) (370 . 13) (100 . "AcDbLine") (10 7929.8642533937
2816.742081448 0.0) (11 7929.8642533937 2703.6199095023 0.0))
((0 . "LINE") (100 . "AcDbEntity") (8 . "ARCH") (62 . 7) (370 . 13) (100 . "AcDbLine") (10 7929.8642533937
2703.6199095023 0.0) (11 7929.8642533937 158.371040724 0.0))
((0 . "LINE") (100 . "AcDbEntity") (8 . "ARCH") (62 . 7) (370 . 13) (100 . "AcDbLine") (10 7929.8642533937 158.371040724
0.0) (11 7929.8642533937 101.8099547511 0.0))
((0 . "LINE") (100 . "AcDbEntity") (8 . "ARCH") (62 . 7) (370 . 13) (100 . "AcDbLine") (10 7929.8642533937
101.8099547511 0.0) (11 7929.8642533937 45.2488687783 0.0))
((0 . "LINE") (100 . "AcDbEntity") (8 . "ARCH") (62 . 7) (370 . 13) (100 . "AcDbLine") (10 7929.8642533937 45.2488687783
0.0) (11 7929.8642533937 0.0 0.0))
((0 . "LINE") (100 . "AcDbEntity") (8 . "ARCH") (62 . 7) (370 . 13) (100 . "AcDbLine") (10 2782.8054298643
3789.592760181 0.0) (11 3940.4223190045 3789.592760181 0.0))
((0 . "LINE") (100 . "AcDbEntity") (8 . "ARCH") (62 . 7) (370 . 13) (100 . "AcDbLine") (10 6846.7194570136
3789.592760181 0.0) (11 7929.8642533937 3789.592760181 0.0))
((0 . "LINE") (100 . "AcDbEntity") (8 . "ARCH") (62 . 7) (370 . 13) (100 . "AcDbLine") (10 7929.8642533937
3789.592760181 0.0) (11 8020.3619909502 3789.592760181 0.0))
((0 . "LINE") (100 . "AcDbEntity") (8 . "ARCH") (62 . 7) (370 . 13) (100 . "AcDbLine") (10 8020.3619909502
3789.592760181 0.0) (11 8020.3619909502 3721.7194570136 0.0))
((0 . "LINE") (100 . "AcDbEntity") (8 . "ARCH") (62 . 7) (370 . 13) (100 . "AcDbLine") (10 8020.3619909502
3721.7194570136 0.0) (11 6787.3303167421 3721.7194570136 0.0))
((0 . "LINE") (100 . "AcDbEntity") (8 . "ARCH") (62 . 7) (370 . 13) (100 . "AcDbLine") (10 6787.3303167421
3721.7194570136 0.0) (11 6628.1737104072 3721.7194570136 0.0))
((0 . "LINE") (100 . "AcDbEntity") (8 . "ARCH") (62 . 7) (370 . 13) (100 . "AcDbLine") (10 6335.6271945701
3721.7194570136 0.0) (11 6230.5661877828 3721.7194570136 0.0))
((0 . "LINE") (100 . "AcDbEntity") (8 . "ARCH") (62 . 7) (370 . 13) (100 . "AcDbLine") (10 5828.257341629
3721.7194570136 0.0) (11 5149.3674434389 3721.7194570136 0.0))
((0 . "LINE") (100 . "AcDbEntity") (8 . "ARCH") (62 . 7) (370 . 13) (100 . "AcDbLine") (10 4873.2569909502
3721.7194570136 0.0) (11 4569.1073642534 3721.7194570136 0.0))
((0 . "LINE") (100 . "AcDbEntity") (8 . "ARCH") (62 . 7) (370 . 13) (100 . "AcDbLine") (10 4254.4220475113
3721.7194570136 0.0) (11 4038.4615384615 3721.7194570136 0.0))
((0 . "LINE") (100 . "AcDbEntity") (8 . "ARCH") (62 . 7) (370 . 13) (100 . "AcDbLine") (10 4038.4615384615
3721.7194570136 0.0) (11 2726.2443438914 3721.7194570136 0.0))
((0 . "LINE") (100 . "AcDbEntity") (8 . "ARCH") (62 . 7) (370 . 13) (100 . "AcDbLine") (10 2726.2443438914
3721.7194570136 0.0) (11 2726.2443438914 3744.3438914027 0.0))
((0 . "LINE") (100 . "AcDbEntity") (8 . "ARCH") (62 . 7) (370 . 13) (100 . "AcDbLine") (10 2726.2443438914
3721.7194570136 0.0) (11 2771.4932126697 3642.5339366516 0.0))
((0 . "LINE") (100 . "AcDbEntity") (8 . "ARCH") (62 . 7) (370 . 13) (100 . "AcDbLine") (10 2771.4932126697
3642.5339366516 0.0) (11 2771.4932126697 3585.9728506787 0.0))
((0 . "LINE") (100 . "AcDbEntity") (8 . "ARCH") (62 . 7) (370 . 13) (100 . "AcDbLine") (10 2771.4932126697
3585.9728506787 0.0) (11 2782.8054298643 3585.9728506787 0.0))
((0 . "LINE") (100 . "AcDbEntity") (8 . "ARCH") (62 . 7) (370 . 13) (100 . "AcDbLine") (10 2782.8054298643
3585.9728506787 0.0) (11 4038.4615384615 3585.9728506787 0.0))
((0 . "LINE") (100 . "AcDbEntity") (8 . "ARCH") (62 . 7) (370 . 13) (100 . "AcDbLine") (10 4038.4615384615
3585.9728506787 0.0) (11 4266.7626470588 3585.9728506787 0.0))
((0 . "LINE") (100 . "AcDbEntity") (8 . "ARCH") (62 . 7) (370 . 13) (100 . "AcDbLine") (10 4556.7667647059
3585.9728506787 0.0) (11 4885.2617986425 3585.9728506787 0.0))
((0 . "LINE") (100 . "AcDbEntity") (8 . "ARCH") (62 . 7) (370 . 13) (100 . "AcDbLine") (10 5137.3626357466
3585.9728506787 0.0) (11 5844.7905769231 3585.9728506787 0.0))
((0 . "LINE") (100 . "AcDbEntity") (8 . "ARCH") (62 . 7) (370 . 13) (100 . "AcDbLine") (10 6214.0329524887
3585.9728506787 0.0) (11 6348.8247850679 3585.9728506787 0.0))
((0 . "LINE") (100 . "AcDbEntity") (8 . "ARCH") (62 . 7) (370 . 13) (100 . "AcDbLine") (10 6614.9761199095
3585.9728506787 0.0) (11 6787.3303167421 3585.9728506787 0.0))
((0 . "LINE") (100 . "AcDbEntity") (8 . "ARCH") (62 . 7) (370 . 13) (100 . "AcDbLine") (10 6787.3303167421
3585.9728506787 0.0) (11 7929.8642533937 3585.9728506787 0.0))
((0 . "LINE") (100 . "AcDbEntity") (8 . "ARCH") (62 . 7) (370 . 13) (100 . "AcDbLine") (10 7929.8642533937
3585.9728506787 0.0) (11 7963.8009049774 3585.9728506787 0.0))
((0 . "LINE") (100 . "AcDbEntity") (8 . "ARCH") (62 . 7) (370 . 13) (100 . "AcDbLine") (10 7963.8009049774
3585.9728506787 0.0) (11 7963.8009049774 3642.5339366516 0.0))
((0 . "LINE") (100 . "AcDbEntity") (8 . "ARCH") (62 . 7) (370 . 13) (100 . "AcDbLine") (10 7963.8009049774
3642.5339366516 0.0) (11 8020.3619909502 3721.7194570136 0.0))
((0 . "LINE") (100 . "AcDbEntity") (8 . "ARCH") (62 . 7) (370 . 13) (100 . "AcDbLine") (10 2782.8054298643
5814.4796380091 0.0) (11 4004.5248868778 5814.4796380091 0.0))
((0 . "LINE") (100 . "AcDbEntity") (8 . "ARCH") (62 . 7) (370 . 13) (100 . "AcDbLine") (10 6843.8914027149
5814.4796380091 0.0) (11 7929.8642533937 5814.4796380091 0.0))
((0 . "LINE") (100 . "AcDbEntity") (8 . "ARCH") (62 . 7) (370 . 13) (100 . "AcDbLine") (10 2782.8054298643
5746.6063348416 0.0) (11 4038.4615384615 5746.6063348416 0.0))
((0 . "LINE") (100 . "AcDbEntity") (8 . "ARCH") (62 . 7) (370 . 13) (100 . "AcDbLine") (10 6787.3303167421
5746.6063348416 0.0) (11 7929.8642533937 5746.6063348416 0.0))
((0 . "LINE") (100 . "AcDbEntity") (8 . "ARCH") (62 . 7) (370 . 13) (100 . "AcDbLine") (10 2782.8054298643
5610.8597285068 0.0) (11 3235.2941176471 5610.8597285068 0.0))
((0 . "LINE") (100 . "AcDbEntity") (8 . "ARCH") (62 . 7) (370 . 13) (100 . "AcDbLine") (10 3235.2941176471
5610.8597285068 0.0) (11 3285.8031674208 5610.8597285068 0.0))
((0 . "LINE") (100 . "AcDbEntity") (8 . "ARCH") (62 . 7) (370 . 13) (100 . "AcDbLine") (10 3285.8031674208
5610.8597285068 0.0) (11 3315.9615384615 5610.8597285068 0.0))
((0 . "LINE") (100 . "AcDbEntity") (8 . "ARCH") (62 . 7) (370 . 13) (100 . "AcDbLine") (10 3315.9615384615
5610.8597285068 0.0) (11 3362.0814479638 5610.8597285068 0.0))
((0 . "LINE") (100 . "AcDbEntity") (8 . "ARCH") (62 . 7) (370 . 13) (100 . "AcDbLine") (10 3362.0814479638
5610.8597285068 0.0) (11 3390.8823529412 5610.8597285068 0.0))
((0 . "LINE") (100 . "AcDbEntity") (8 . "ARCH") (62 . 7) (370 . 13) (100 . "AcDbLine") (10 3390.8823529412
5610.8597285068 0.0) (11 3440.7126696833 5610.8597285068 0.0))
((0 . "LINE") (100 . "AcDbEntity") (8 . "ARCH") (62 . 7) (370 . 13) (100 . "AcDbLine") (10 3440.7126696833
5610.8597285068 0.0) (11 3507.0701357466 5610.8597285068 0.0))
((0 . "LINE") (100 . "AcDbEntity") (8 . "ARCH") (62 . 7) (370 . 13) (100 . "AcDbLine") (10 3507.0701357466
5610.8597285068 0.0) (11 3526.1538461538 5610.8597285068 0.0))
((0 . "LINE") (100 . "AcDbEntity") (8 . "ARCH") (62 . 7) (370 . 13) (100 . "AcDbLine") (10 3526.1538461538
5610.8597285068 0.0) (11 3573.5520361991 5610.8597285068 0.0))
((0 . "LINE") (100 . "AcDbEntity") (8 . "ARCH") (62 . 7) (370 . 13) (100 . "AcDbLine") (10 3573.5520361991
5610.8597285068 0.0) (11 3643.2352941176 5610.8597285068 0.0))
((0 . "LINE") (100 . "AcDbEntity") (8 . "ARCH") (62 . 7) (370 . 13) (100 . "AcDbLine") (10 3643.2352941176
5610.8597285068 0.0) (11 3663.9819004525 5610.8597285068 0.0))
((0 . "LINE") (100 . "AcDbEntity") (8 . "ARCH") (62 . 7) (370 . 13) (100 . "AcDbLine") (10 3663.9819004525
5610.8597285068 0.0) (11 3712.1380090498 5610.8597285068 0.0))
((0 . "LINE") (100 . "AcDbEntity") (8 . "ARCH") (62 . 7) (370 . 13) (100 . "AcDbLine") (10 3712.1380090498
5610.8597285068 0.0) (11 3739.8076923077 5610.8597285068 0.0))
((0 . "LINE") (100 . "AcDbEntity") (8 . "ARCH") (62 . 7) (370 . 13) (100 . "AcDbLine") (10 3739.8076923077
5610.8597285068 0.0) (11 3791.4705882353 5610.8597285068 0.0))
((0 . "LINE") (100 . "AcDbEntity") (8 . "ARCH") (62 . 7) (370 . 13) (100 . "AcDbLine") (10 3791.4705882353
5610.8597285068 0.0) (11 3800.9049773756 5610.8597285068 0.0))
((0 . "LINE") (100 . "AcDbEntity") (8 . "ARCH") (62 . 7) (370 . 13) (100 . "AcDbLine") (10 3800.9049773756
5610.8597285068 0.0) (11 4162.8959276018 5610.8597285068 0.0))
((0 . "LINE") (100 . "AcDbEntity") (8 . "ARCH") (62 . 7) (370 . 13) (100 . "AcDbLine") (10 6708.1447963801
5610.8597285068 0.0) (11 7047.5113122172 5610.8597285068 0.0))
((0 . "LINE") (100 . "AcDbEntity") (8 . "ARCH") (62 . 7) (370 . 13) (100 . "AcDbLine") (10 7047.5113122172
5610.8597285068 0.0) (11 7096.7647058824 5610.8597285068 0.0))
((0 . "LINE") (100 . "AcDbEntity") (8 . "ARCH") (62 . 7) (370 . 13) (100 . "AcDbLine") (10 7096.7647058824
5610.8597285068 0.0) (11 7127.8959276018 5610.8597285068 0.0))
((0 . "LINE") (100 . "AcDbEntity") (8 . "ARCH") (62 . 7) (370 . 13) (100 . "AcDbLine") (10 7127.8959276018
5610.8597285068 0.0) (11 7172.2058823529 5610.8597285068 0.0))
((0 . "LINE") (100 . "AcDbEntity") (8 . "ARCH") (62 . 7) (370 . 13) (100 . "AcDbLine") (10 7172.2058823529
5610.8597285068 0.0) (11 7202.0701357466 5610.8597285068 0.0))
((0 . "LINE") (100 . "AcDbEntity") (8 . "ARCH") (62 . 7) (370 . 13) (100 . "AcDbLine") (10 7202.0701357466
5610.8597285068 0.0) (11 7246.0972850679 5610.8597285068 0.0))
((0 . "LINE") (100 . "AcDbEntity") (8 . "ARCH") (62 . 7) (370 . 13) (100 . "AcDbLine") (10 7246.0972850679
5610.8597285068 0.0) (11 7273.778280543 5610.8597285068 0.0))
((0 . "LINE") (100 . "AcDbEntity") (8 . "ARCH") (62 . 7) (370 . 13) (100 . "AcDbLine") (10 7273.778280543
5610.8597285068 0.0) (11 7322.4321266968 5610.8597285068 0.0))
((0 . "LINE") (100 . "AcDbEntity") (8 . "ARCH") (62 . 7) (370 . 13) (100 . "AcDbLine") (10 7322.4321266968
5610.8597285068 0.0) (11 7349.9321266968 5610.8597285068 0.0))
((0 . "LINE") (100 . "AcDbEntity") (8 . "ARCH") (62 . 7) (370 . 13) (100 . "AcDbLine") (10 7349.9321266968
5610.8597285068 0.0) (11 7393.7330316742 5610.8597285068 0.0))
((0 . "LINE") (100 . "AcDbEntity") (8 . "ARCH") (62 . 7) (370 . 13) (100 . "AcDbLine") (10 7393.7330316742
5610.8597285068 0.0) (11 7424.4909502262 5610.8597285068 0.0))
((0 . "LINE") (100 . "AcDbEntity") (8 . "ARCH") (62 . 7) (370 . 13) (100 . "AcDbLine") (10 7424.4909502262
5610.8597285068 0.0) (11 7463.6425339367 5610.8597285068 0.0))
((0 . "LINE") (100 . "AcDbEntity") (8 . "ARCH") (62 . 7) (370 . 13) (100 . "AcDbLine") (10 7463.6425339367
5610.8597285068 0.0) (11 7501.3800904977 5610.8597285068 0.0))
((0 . "LINE") (100 . "AcDbEntity") (8 . "ARCH") (62 . 7) (370 . 13) (100 . "AcDbLine") (10 7501.3800904977
5610.8597285068 0.0) (11 7529.7171945701 5610.8597285068 0.0))
((0 . "LINE") (100 . "AcDbEntity") (8 . "ARCH") (62 . 7) (370 . 13) (100 . "AcDbLine") (10 7529.7171945701
5610.8597285068 0.0) (11 7579.185520362 5610.8597285068 0.0))
((0 . "LINE") (100 . "AcDbEntity") (8 . "ARCH") (62 . 7) (370 . 13) (100 . "AcDbLine") (10 7579.185520362
5610.8597285068 0.0) (11 7929.8642533937 5610.8597285068 0.0))
((0 . "LINE") (100 . "AcDbEntity") (8 . "ARCH") (62 . 7) (370 . 13) (100 . "AcDbLine") (10 12036.1990950226
6481.9004524887 0.0) (11 12036.1990950226 6470.5882352941 0.0))
((0 . "LINE") (100 . "AcDbEntity") (8 . "ARCH") (62 . 7) (370 . 13) (100 . "AcDbLine") (10 12036.1990950226
6470.5882352941 0.0) (11 12036.1990950226 6199.0950226244 0.0))
((0 . "LINE") (100 . "AcDbEntity") (8 . "ARCH") (62 . 7) (370 . 13) (100 . "AcDbLine") (10 12036.1990950226
6199.0950226244 0.0) (11 12036.1990950226 5814.4796380091 0.0))
((0 . "LINE") (100 . "AcDbEntity") (8 . "ARCH") (62 . 7) (370 . 13) (100 . "AcDbLine") (10 12036.1990950226
5814.4796380091 0.0) (11 12036.1990950226 5746.6063348416 0.0))
((0 . "LINE") (100 . "AcDbEntity") (8 . "ARCH") (62 . 7) (370 . 13) (100 . "AcDbLine") (10 12036.1990950226
5746.6063348416 0.0) (11 12036.1990950226 5735.2941176471 0.0))
((0 . "LINE") (100 . "AcDbEntity") (8 . "ARCH") (62 . 7) (370 . 13) (100 . "AcDbLine") (10 12036.1990950226
5735.2941176471 0.0) (11 12036.1990950226 5610.8597285068 0.0))
((0 . "LINE") (100 . "AcDbEntity") (8 . "ARCH") (62 . 7) (370 . 13) (100 . "AcDbLine") (10 12036.1990950226
5610.8597285068 0.0) (11 12036.1990950226 5599.5475113122 0.0))
((0 . "LINE") (100 . "AcDbEntity") (8 . "ARCH") (62 . 7) (370 . 13) (100 . "AcDbLine") (10 12036.1990950226
5599.5475113122 0.0) (11 12036.1990950226 4909.5022624434 0.0))
((0 . "LINE") (100 . "AcDbEntity") (8 . "ARCH") (62 . 7) (370 . 13) (100 . "AcDbLine") (10 12036.1990950226
4909.5022624434 0.0) (11 12036.1990950226 3789.592760181 0.0))
((0 . "LINE") (100 . "AcDbEntity") (8 . "ARCH") (62 . 7) (370 . 13) (100 . "AcDbLine") (10 17239.8190045249
6481.9004524887 0.0) (11 17239.8190045249 6199.0950226244 0.0))
((0 . "LINE") (100 . "AcDbEntity") (8 . "ARCH") (62 . 7) (370 . 13) (100 . "AcDbLine") (10 17239.8190045249
6199.0950226244 0.0) (11 17239.8190045249 5814.4796380091 0.0))
((0 . "LINE") (100 . "AcDbEntity") (8 . "ARCH") (62 . 7) (370 . 13) (100 . "AcDbLine") (10 17239.8190045249
5814.4796380091 0.0) (11 17239.8190045249 5803.1674208145 0.0))
((0 . "LINE") (100 . "AcDbEntity") (8 . "ARCH") (62 . 7) (370 . 13) (100 . "AcDbLine") (10 17239.8190045249
5803.1674208145 0.0) (11 17239.8190045249 5746.6063348416 0.0))
((0 . "LINE") (100 . "AcDbEntity") (8 . "ARCH") (62 . 7) (370 . 13) (100 . "AcDbLine") (10 17239.8190045249
5746.6063348416 0.0) (11 17239.8190045249 5667.4208144796 0.0))
((0 . "LINE") (100 . "AcDbEntity") (8 . "ARCH") (62 . 7) (370 . 13) (100 . "AcDbLine") (10 17239.8190045249
5667.4208144796 0.0) (11 17239.8190045249 5622.1719457014 0.0))
((0 . "LINE") (100 . "AcDbEntity") (8 . "ARCH") (62 . 7) (370 . 13) (100 . "AcDbLine") (10 12036.1990950226
3597.2850678733 0.0) (11 12036.1990950226 3585.9728506787 0.0))
((0 . "LINE") (100 . "AcDbEntity") (8 . "ARCH") (62 . 7) (370 . 13) (100 . "AcDbLine") (10 12036.1990950226
3585.9728506787 0.0) (11 12036.1990950226 2816.742081448 0.0))
((0 . "LINE") (100 . "AcDbEntity") (8 . "ARCH") (62 . 7) (370 . 13) (100 . "AcDbLine") (10 12036.1990950226
2816.742081448 0.0) (11 12036.1990950226 2703.6199095023 0.0))
((0 . "LINE") (100 . "AcDbEntity") (8 . "ARCH") (62 . 7) (370 . 13) (100 . "AcDbLine") (10 12036.1990950226
2703.6199095023 0.0) (11 12036.1990950226 2070.525723721 0.0))
((0 . "LINE") (100 . "AcDbEntity") (8 . "ARCH") (62 . 7) (370 . 13) (100 . "AcDbLine") (10 12036.1990950226
2070.525723721 0.0) (11 12036.1990950226 192.3076923077 0.0))
((0 . "LINE") (100 . "AcDbEntity") (8 . "ARCH") (62 . 7) (370 . 13) (100 . "AcDbLine") (10 12036.1990950226
192.3076923077 0.0) (11 12036.1990950226 158.371040724 0.0))
((0 . "LINE") (100 . "AcDbEntity") (8 . "ARCH") (62 . 7) (370 . 13) (100 . "AcDbLine") (10 12036.1990950226
158.371040724 0.0) (11 12036.1990950226 101.8099547511 0.0))
((0 . "LINE") (100 . "AcDbEntity") (8 . "ARCH") (62 . 7) (370 . 13) (100 . "AcDbLine") (10 12036.1990950226
101.8099547511 0.0) (11 12036.1990950226 45.2488687783 0.0))
((0 . "LINE") (100 . "AcDbEntity") (8 . "ARCH") (62 . 7) (370 . 13) (100 . "AcDbLine") (10 12036.1990950226
45.2488687783 0.0) (11 12036.1990950226 0.0 0.0))
((0 . "LINE") (100 . "AcDbEntity") (8 . "ARCH") (62 . 7) (370 . 13) (100 . "AcDbLine") (10 17239.8190045249
2997.7375565611 0.0) (11 17239.8190045249 2861.9909502262 0.0))
((0 . "LINE") (100 . "AcDbEntity") (8 . "ARCH") (62 . 7) (370 . 13) (100 . "AcDbLine") (10 17239.8190045249
2861.9909502262 0.0) (11 17239.8190045249 2805.4298642534 0.0))
((0 . "LINE") (100 . "AcDbEntity") (8 . "ARCH") (62 . 7) (370 . 13) (100 . "AcDbLine") (10 11979.6380090498
3789.592760181 0.0) (11 12036.1990950226 3789.592760181 0.0))
((0 . "LINE") (100 . "AcDbEntity") (8 . "ARCH") (62 . 7) (370 . 13) (100 . "AcDbLine") (10 12036.1990950226
3789.592760181 0.0) (11 13092.0060294118 3789.592760181 0.0))
((0 . "LINE") (100 . "AcDbEntity") (8 . "ARCH") (62 . 7) (370 . 13) (100 . "AcDbLine") (10 15998.3031674208
3789.592760181 0.0) (11 17239.8190045249 3789.592760181 0.0))
((0 . "LINE") (100 . "AcDbEntity") (8 . "ARCH") (62 . 7) (370 . 13) (100 . "AcDbLine") (10 17239.8190045249
3789.592760181 0.0) (11 17285.0678733032 3789.592760181 0.0))
((0 . "LINE") (100 . "AcDbEntity") (8 . "ARCH") (62 . 7) (370 . 13) (100 . "AcDbLine") (10 17330.3167420814
3744.3438914027 0.0) (11 17330.3167420814 3721.7194570136 0.0))
((0 . "LINE") (100 . "AcDbEntity") (8 . "ARCH") (62 . 7) (370 . 13) (100 . "AcDbLine") (10 17330.3167420814
3721.7194570136 0.0) (11 17239.8190045249 3721.7194570136 0.0))
((0 . "LINE") (100 . "AcDbEntity") (8 . "ARCH") (62 . 7) (370 . 13) (100 . "AcDbLine") (10 17239.8190045249
3721.7194570136 0.0) (11 15938.9140271493 3721.7194570136 0.0))
((0 . "LINE") (100 . "AcDbEntity") (8 . "ARCH") (62 . 7) (370 . 13) (100 . "AcDbLine") (10 15938.9140271493
3721.7194570136 0.0) (11 15779.7574208145 3721.7194570136 0.0))
((0 . "LINE") (100 . "AcDbEntity") (8 . "ARCH") (62 . 7) (370 . 13) (100 . "AcDbLine") (10 15487.2109049774
3721.7194570136 0.0) (11 15382.14989819 3721.7194570136 0.0))
((0 . "LINE") (100 . "AcDbEntity") (8 . "ARCH") (62 . 7) (370 . 13) (100 . "AcDbLine") (10 14979.8410520362
3721.7194570136 0.0) (11 14300.9511538462 3721.7194570136 0.0))
((0 . "LINE") (100 . "AcDbEntity") (8 . "ARCH") (62 . 7) (370 . 13) (100 . "AcDbLine") (10 14024.8407013575
3721.7194570136 0.0) (11 13720.6910746606 3721.7194570136 0.0))
((0 . "LINE") (100 . "AcDbEntity") (8 . "ARCH") (62 . 7) (370 . 13) (100 . "AcDbLine") (10 13406.0057579186
3721.7194570136 0.0) (11 13190.0452488688 3721.7194570136 0.0))
((0 . "LINE") (100 . "AcDbEntity") (8 . "ARCH") (62 . 7) (370 . 13) (100 . "AcDbLine") (10 13190.0452488688
3721.7194570136 0.0) (11 11979.6380090498 3721.7194570136 0.0))
((0 . "LINE") (100 . "AcDbEntity") (8 . "ARCH") (62 . 7) (370 . 13) (100 . "AcDbLine") (10 11979.6380090498
3721.7194570136 0.0) (11 11979.6380090498 3789.592760181 0.0))
((0 . "LINE") (100 . "AcDbEntity") (8 . "ARCH") (62 . 7) (370 . 13) (100 . "AcDbLine") (10 11979.6380090498
3721.7194570136 0.0) (11 12024.8868778281 3642.5339366516 0.0))
((0 . "LINE") (100 . "AcDbEntity") (8 . "ARCH") (62 . 7) (370 . 13) (100 . "AcDbLine") (10 12024.8868778281
3642.5339366516 0.0) (11 12024.8868778281 3585.9728506787 0.0))
((0 . "LINE") (100 . "AcDbEntity") (8 . "ARCH") (62 . 7) (370 . 13) (100 . "AcDbLine") (10 12024.8868778281
3585.9728506787 0.0) (11 12036.1990950226 3585.9728506787 0.0))
((0 . "LINE") (100 . "AcDbEntity") (8 . "ARCH") (62 . 7) (370 . 13) (100 . "AcDbLine") (10 12036.1990950226
3585.9728506787 0.0) (11 13190.0452488688 3585.9728506787 0.0))
((0 . "LINE") (100 . "AcDbEntity") (8 . "ARCH") (62 . 7) (370 . 13) (100 . "AcDbLine") (10 13190.0452488688
3585.9728506787 0.0) (11 13418.3463574661 3585.9728506787 0.0))
((0 . "LINE") (100 . "AcDbEntity") (8 . "ARCH") (62 . 7) (370 . 13) (100 . "AcDbLine") (10 13708.3504751131
3585.9728506787 0.0) (11 14036.8455090498 3585.9728506787 0.0))
((0 . "LINE") (100 . "AcDbEntity") (8 . "ARCH") (62 . 7) (370 . 13) (100 . "AcDbLine") (10 14288.9463461538
3585.9728506787 0.0) (11 14996.3742873303 3585.9728506787 0.0))
((0 . "LINE") (100 . "AcDbEntity") (8 . "ARCH") (62 . 7) (370 . 13) (100 . "AcDbLine") (10 15365.6166628959
3585.9728506787 0.0) (11 15500.4084954751 3585.9728506787 0.0))
((0 . "LINE") (100 . "AcDbEntity") (8 . "ARCH") (62 . 7) (370 . 13) (100 . "AcDbLine") (10 15766.5598303167
3585.9728506787 0.0) (11 15938.9140271493 3585.9728506787 0.0))
((0 . "LINE") (100 . "AcDbEntity") (8 . "ARCH") (62 . 7) (370 . 13) (100 . "AcDbLine") (10 15938.9140271493
3585.9728506787 0.0) (11 17239.8190045249 3585.9728506787 0.0))
((0 . "LINE") (100 . "AcDbEntity") (8 . "ARCH") (62 . 7) (370 . 13) (100 . "AcDbLine") (10 17239.8190045249
3585.9728506787 0.0) (11 17273.7556561086 3585.9728506787 0.0))
((0 . "LINE") (100 . "AcDbEntity") (8 . "ARCH") (62 . 7) (370 . 13) (100 . "AcDbLine") (10 17273.7556561086
3585.9728506787 0.0) (11 17273.7556561086 3642.5339366516 0.0))
((0 . "LINE") (100 . "AcDbEntity") (8 . "ARCH") (62 . 7) (370 . 13) (100 . "AcDbLine") (10 17273.7556561086
3642.5339366516 0.0) (11 17330.3167420814 3721.7194570136 0.0))
((0 . "LINE") (100 . "AcDbEntity") (8 . "ARCH") (62 . 7) (370 . 13) (100 . "AcDbLine") (10 12036.1990950226
5814.4796380091 0.0) (11 13156.1085972851 5814.4796380091 0.0))
((0 . "LINE") (100 . "AcDbEntity") (8 . "ARCH") (62 . 7) (370 . 13) (100 . "AcDbLine") (10 15995.4751131222
5814.4796380091 0.0) (11 17239.8190045249 5814.4796380091 0.0))
((0 . "LINE") (100 . "AcDbEntity") (8 . "ARCH") (62 . 7) (370 . 13) (100 . "AcDbLine") (10 12036.1990950226
5746.6063348416 0.0) (11 13190.0452488688 5746.6063348416 0.0))
((0 . "LINE") (100 . "AcDbEntity") (8 . "ARCH") (62 . 7) (370 . 13) (100 . "AcDbLine") (10 15938.9140271493
5746.6063348416 0.0) (11 17239.8190045249 5746.6063348416 0.0))
((0 . "LINE") (100 . "AcDbEntity") (8 . "ARCH") (62 . 7) (370 . 13) (100 . "AcDbLine") (10 12036.1990950226
5610.8597285068 0.0) (11 12420.814479638 5610.8597285068 0.0))
((0 . "LINE") (100 . "AcDbEntity") (8 . "ARCH") (62 . 7) (370 . 13) (100 . "AcDbLine") (10 12420.814479638
5610.8597285068 0.0) (11 12478.4162895928 5610.8597285068 0.0))
((0 . "LINE") (100 . "AcDbEntity") (8 . "ARCH") (62 . 7) (370 . 13) (100 . "AcDbLine") (10 12478.4162895928
5610.8597285068 0.0) (11 12505.7918552036 5610.8597285068 0.0))
((0 . "LINE") (100 . "AcDbEntity") (8 . "ARCH") (62 . 7) (370 . 13) (100 . "AcDbLine") (10 12505.7918552036
5610.8597285068 0.0) (11 12552.0022624434 5610.8597285068 0.0))
((0 . "LINE") (100 . "AcDbEntity") (8 . "ARCH") (62 . 7) (370 . 13) (100 . "AcDbLine") (10 12552.0022624434
5610.8597285068 0.0) (11 12642.3076923077 5610.8597285068 0.0))
((0 . "LINE") (100 . "AcDbEntity") (8 . "ARCH") (62 . 7) (370 . 13) (100 . "AcDbLine") (10 12642.3076923077
5610.8597285068 0.0) (11 12695.1583710407 5610.8597285068 0.0))
((0 . "LINE") (100 . "AcDbEntity") (8 . "ARCH") (62 . 7) (370 . 13) (100 . "AcDbLine") (10 12695.1583710407
5610.8597285068 0.0) (11 12711.742081448 5610.8597285068 0.0))
((0 . "LINE") (100 . "AcDbEntity") (8 . "ARCH") (62 . 7) (370 . 13) (100 . "AcDbLine") (10 12711.742081448
5610.8597285068 0.0) (11 12761.2556561086 5610.8597285068 0.0))
((0 . "LINE") (100 . "AcDbEntity") (8 . "ARCH") (62 . 7) (370 . 13) (100 . "AcDbLine") (10 12761.2556561086
5610.8597285068 0.0) (11 12790.3054298643 5610.8597285068 0.0))
((0 . "LINE") (100 . "AcDbEntity") (8 . "ARCH") (62 . 7) (370 . 13) (100 . "AcDbLine") (10 12790.3054298643
5610.8597285068 0.0) (11 12820.2941176471 5610.8597285068 0.0))
((0 . "LINE") (100 . "AcDbEntity") (8 . "ARCH") (62 . 7) (370 . 13) (100 . "AcDbLine") (10 12820.2941176471
5610.8597285068 0.0) (11 12864.592760181 5610.8597285068 0.0))
((0 . "LINE") (100 . "AcDbEntity") (8 . "ARCH") (62 . 7) (370 . 13) (100 . "AcDbLine") (10 12864.592760181
5610.8597285068 0.0) (11 12883.3936651584 5610.8597285068 0.0))
((0 . "LINE") (100 . "AcDbEntity") (8 . "ARCH") (62 . 7) (370 . 13) (100 . "AcDbLine") (10 12883.3936651584
5610.8597285068 0.0) (11 12940.6787330317 5610.8597285068 0.0))
((0 . "LINE") (100 . "AcDbEntity") (8 . "ARCH") (62 . 7) (370 . 13) (100 . "AcDbLine") (10 12940.6787330317
5610.8597285068 0.0) (11 12952.4886877828 5610.8597285068 0.0))
((0 . "LINE") (100 . "AcDbEntity") (8 . "ARCH") (62 . 7) (370 . 13) (100 . "AcDbLine") (10 12952.4886877828
5610.8597285068 0.0) (11 13314.4796380091 5610.8597285068 0.0))
((0 . "LINE") (100 . "AcDbEntity") (8 . "ARCH") (62 . 7) (370 . 13) (100 . "AcDbLine") (10 15859.7285067873
5610.8597285068 0.0) (11 16221.7194570136 5610.8597285068 0.0))
((0 . "LINE") (100 . "AcDbEntity") (8 . "ARCH") (62 . 7) (370 . 13) (100 . "AcDbLine") (10 16221.7194570136
5610.8597285068 0.0) (11 16274.2986425339 5610.8597285068 0.0))
((0 . "LINE") (100 . "AcDbEntity") (8 . "ARCH") (62 . 7) (370 . 13) (100 . "AcDbLine") (10 16274.2986425339
5610.8597285068 0.0) (11 16301.6063348416 5610.8597285068 0.0))
((0 . "LINE") (100 . "AcDbEntity") (8 . "ARCH") (62 . 7) (370 . 13) (100 . "AcDbLine") (10 16301.6063348416
5610.8597285068 0.0) (11 16348.3823529412 5610.8597285068 0.0))
((0 . "LINE") (100 . "AcDbEntity") (8 . "ARCH") (62 . 7) (370 . 13) (100 . "AcDbLine") (10 16348.3823529412
5610.8597285068 0.0) (11 16375.4524886878 5610.8597285068 0.0))
((0 . "LINE") (100 . "AcDbEntity") (8 . "ARCH") (62 . 7) (370 . 13) (100 . "AcDbLine") (10 16375.4524886878
5610.8597285068 0.0) (11 16442.3076923077 5610.8597285068 0.0))
((0 . "LINE") (100 . "AcDbEntity") (8 . "ARCH") (62 . 7) (370 . 13) (100 . "AcDbLine") (10 16442.3076923077
5610.8597285068 0.0) (11 16504.536199095 5610.8597285068 0.0))
((0 . "LINE") (100 . "AcDbEntity") (8 . "ARCH") (62 . 7) (370 . 13) (100 . "AcDbLine") (10 16504.536199095
5610.8597285068 0.0) (11 16540.9389140272 5610.8597285068 0.0))
((0 . "LINE") (100 . "AcDbEntity") (8 . "ARCH") (62 . 7) (370 . 13) (100 . "AcDbLine") (10 16540.9389140272
5610.8597285068 0.0) (11 16576.6742081448 5610.8597285068 0.0))
((0 . "LINE") (100 . "AcDbEntity") (8 . "ARCH") (62 . 7) (370 . 13) (100 . "AcDbLine") (10 16576.6742081448
5610.8597285068 0.0) (11 16625.5769230769 5610.8597285068 0.0))
((0 . "LINE") (100 . "AcDbEntity") (8 . "ARCH") (62 . 7) (370 . 13) (100 . "AcDbLine") (10 16625.5769230769
5610.8597285068 0.0) (11 16650.9389140271 5610.8597285068 0.0))
((0 . "LINE") (100 . "AcDbEntity") (8 . "ARCH") (62 . 7) (370 . 13) (100 . "AcDbLine") (10 16650.9389140271
5610.8597285068 0.0) (11 16696.1538461538 5610.8597285068 0.0))
((0 . "LINE") (100 . "AcDbEntity") (8 . "ARCH") (62 . 7) (370 . 13) (100 . "AcDbLine") (10 16696.1538461538
5610.8597285068 0.0) (11 16725.350678733 5610.8597285068 0.0))
((0 . "LINE") (100 . "AcDbEntity") (8 . "ARCH") (62 . 7) (370 . 13) (100 . "AcDbLine") (10 16725.350678733
5610.8597285068 0.0) (11 16773.7556561086 5610.8597285068 0.0))
((0 . "LINE") (100 . "AcDbEntity") (8 . "ARCH") (62 . 7) (370 . 13) (100 . "AcDbLine") (10 16773.7556561086
5610.8597285068 0.0) (11 16787.3303167421 5610.8597285068 0.0))
((0 . "LINE") (100 . "AcDbEntity") (8 . "ARCH") (62 . 7) (370 . 13) (100 . "AcDbLine") (10 16787.3303167421
5610.8597285068 0.0) (11 17239.8190045249 5610.8597285068 0.0))
((0 . "LINE") (100 . "AcDbEntity") (8 . "ARCH") (62 . 7) (370 . 13) (100 . "AcDbLine") (10 9547.5113122172
6425.3393665158 0.0) (11 10452.4886877828 6425.3393665158 0.0))
((0 . "LINE") (100 . "AcDbEntity") (8 . "ARCH") (62 . 7) (370 . 13) (100 . "AcDbLine") (10 10452.4886877828
6425.3393665158 0.0) (11 10452.4886877828 6199.0950226244 0.0))
((0 . "LINE") (100 . "AcDbEntity") (8 . "ARCH") (62 . 7) (370 . 13) (100 . "AcDbLine") (10 10452.4886877828
6199.0950226244 0.0) (11 10452.4886877828 5814.4796380091 0.0))
((0 . "LINE") (100 . "AcDbEntity") (8 . "ARCH") (62 . 7) (370 . 13) (100 . "AcDbLine") (10 10452.4886877828
5814.4796380091 0.0) (11 10452.4886877828 5735.2941176471 0.0))
((0 . "LINE") (100 . "AcDbEntity") (8 . "ARCH") (62 . 7) (370 . 13) (100 . "AcDbLine") (10 10452.4886877828
5735.2941176471 0.0) (11 10452.4886877828 5599.5475113122 0.0))
((0 . "LINE") (100 . "AcDbEntity") (8 . "ARCH") (62 . 7) (370 . 13) (100 . "AcDbLine") (10 10452.4886877828
5599.5475113122 0.0) (11 10452.4886877828 4909.5022624434 0.0))
((0 . "LINE") (100 . "AcDbEntity") (8 . "ARCH") (62 . 7) (370 . 13) (100 . "AcDbLine") (10 10452.4886877828
4909.5022624434 0.0) (11 10452.4886877828 2816.742081448 0.0))
((0 . "LINE") (100 . "AcDbEntity") (8 . "ARCH") (62 . 7) (370 . 13) (100 . "AcDbLine") (10 10452.4886877828
2816.742081448 0.0) (11 10452.4886877828 2703.6199095023 0.0))
((0 . "LINE") (100 . "AcDbEntity") (8 . "ARCH") (62 . 7) (370 . 13) (100 . "AcDbLine") (10 10452.4886877828
2703.6199095023 0.0) (11 10452.4886877828 158.371040724 0.0))
((0 . "LINE") (100 . "AcDbEntity") (8 . "ARCH") (62 . 7) (370 . 13) (100 . "AcDbLine") (10 10452.4886877828
158.371040724 0.0) (11 10452.4886877828 101.8099547511 0.0))
((0 . "LINE") (100 . "AcDbEntity") (8 . "ARCH") (62 . 7) (370 . 13) (100 . "AcDbLine") (10 10452.4886877828
101.8099547511 0.0) (11 10452.4886877828 45.2488687783 0.0))
((0 . "LINE") (100 . "AcDbEntity") (8 . "ARCH") (62 . 7) (370 . 13) (100 . "AcDbLine") (10 10452.4886877828
45.2488687783 0.0) (11 10452.4886877828 0.0 0.0))
((0 . "LINE") (100 . "AcDbEntity") (8 . "ARCH") (62 . 7) (370 . 13) (100 . "AcDbLine") (10 9547.5113122172 0.0 0.0) (11
9547.5113122172 45.2488687783 0.0))
((0 . "LINE") (100 . "AcDbEntity") (8 . "ARCH") (62 . 7) (370 . 13) (100 . "AcDbLine") (10 9547.5113122172 45.2488687783
0.0) (11 9547.5113122172 101.8099547511 0.0))
((0 . "LINE") (100 . "AcDbEntity") (8 . "ARCH") (62 . 7) (370 . 13) (100 . "AcDbLine") (10 9547.5113122172
101.8099547511 0.0) (11 9547.5113122172 158.371040724 0.0))
((0 . "LINE") (100 . "AcDbEntity") (8 . "ARCH") (62 . 7) (370 . 13) (100 . "AcDbLine") (10 9547.5113122172 158.371040724
0.0) (11 9547.5113122172 192.3076923077 0.0))
((0 . "LINE") (100 . "AcDbEntity") (8 . "ARCH") (62 . 7) (370 . 13) (100 . "AcDbLine") (10 9547.5113122172
192.3076923077 0.0) (11 9547.5113122172 2058.8235294118 0.0))
((0 . "LINE") (100 . "AcDbEntity") (8 . "ARCH") (62 . 7) (370 . 13) (100 . "AcDbLine") (10 9547.5113122172
2058.8235294118 0.0) (11 9547.5113122172 2703.6199095023 0.0))
((0 . "LINE") (100 . "AcDbEntity") (8 . "ARCH") (62 . 7) (370 . 13) (100 . "AcDbLine") (10 9547.5113122172
2703.6199095023 0.0) (11 9547.5113122172 2816.742081448 0.0))
((0 . "LINE") (100 . "AcDbEntity") (8 . "ARCH") (62 . 7) (370 . 13) (100 . "AcDbLine") (10 9547.5113122172
2816.742081448 0.0) (11 9547.5113122172 4909.5022624434 0.0))
((0 . "LINE") (100 . "AcDbEntity") (8 . "ARCH") (62 . 7) (370 . 13) (100 . "AcDbLine") (10 9547.5113122172
4909.5022624434 0.0) (11 9547.5113122172 5599.5475113122 0.0))
((0 . "LINE") (100 . "AcDbEntity") (8 . "ARCH") (62 . 7) (370 . 13) (100 . "AcDbLine") (10 9547.5113122172
5599.5475113122 0.0) (11 9547.5113122172 5735.2941176471 0.0))
((0 . "LINE") (100 . "AcDbEntity") (8 . "ARCH") (62 . 7) (370 . 13) (100 . "AcDbLine") (10 9547.5113122172
5735.2941176471 0.0) (11 9547.5113122172 5814.4796380091 0.0))
((0 . "LINE") (100 . "AcDbEntity") (8 . "ARCH") (62 . 7) (370 . 13) (100 . "AcDbLine") (10 9547.5113122172
5814.4796380091 0.0) (11 9547.5113122172 6199.0950226244 0.0))
((0 . "LINE") (100 . "AcDbEntity") (8 . "ARCH") (62 . 7) (370 . 13) (100 . "AcDbLine") (10 9547.5113122172
6199.0950226244 0.0) (11 9547.5113122172 6425.3393665158 0.0))
((0 . "LINE") (100 . "AcDbEntity") (8 . "ARCH") (62 . 7) (370 . 13) (100 . "AcDbLine") (10 9377.8280542986
6809.9547511312 0.0) (11 9649.3212669683 6809.9547511312 0.0))
((0 . "LINE") (100 . "AcDbEntity") (8 . "ARCH") (62 . 7) (370 . 13) (100 . "AcDbLine") (10 9649.3212669683
6809.9547511312 0.0) (11 9751.1312217195 6809.9547511312 0.0))
((0 . "LINE") (100 . "AcDbEntity") (8 . "ARCH") (62 . 7) (370 . 13) (100 . "AcDbLine") (10 9751.1312217195
6809.9547511312 0.0) (11 9807.6923076923 6809.9547511312 0.0))
((0 . "LINE") (100 . "AcDbEntity") (8 . "ARCH") (62 . 7) (370 . 13) (100 . "AcDbLine") (10 9807.6923076923
6809.9547511312 0.0) (11 10316.742081448 6809.9547511312 0.0))
((0 . "LINE") (100 . "AcDbEntity") (8 . "ARCH") (62 . 7) (370 . 13) (100 . "AcDbLine") (10 10316.742081448
6809.9547511312 0.0) (11 10373.3031674208 6809.9547511312 0.0))
((0 . "LINE") (100 . "AcDbEntity") (8 . "ARCH") (62 . 7) (370 . 13) (100 . "AcDbLine") (10 10373.3031674208
6809.9547511312 0.0) (11 10475.1131221719 6809.9547511312 0.0))
((0 . "LINE") (100 . "AcDbEntity") (8 . "ARCH") (62 . 7) (370 . 13) (100 . "AcDbLine") (10 10475.1131221719
6809.9547511312 0.0) (11 10633.4841628959 6809.9547511312 0.0))
((0 . "LINE") (100 . "AcDbEntity") (8 . "ARCH") (62 . 7) (370 . 13) (100 . "AcDbLine") (10 10633.4841628959
6809.9547511312 0.0) (11 10633.4841628959 6761.8212669683 0.0))
((0 . "LINE") (100 . "AcDbEntity") (8 . "ARCH") (62 . 7) (370 . 13) (100 . "AcDbLine") (10 10633.4841628959
6761.8212669683 0.0) (11 10633.4841628959 6730.7692307692 0.0))
((0 . "LINE") (100 . "AcDbEntity") (8 . "ARCH") (62 . 7) (370 . 13) (100 . "AcDbLine") (10 10633.4841628959
6730.7692307692 0.0) (11 10619.3438914027 6719.4570135747 0.0))
((0 . "LINE") (100 . "AcDbEntity") (8 . "ARCH") (62 . 7) (370 . 13) (100 . "AcDbLine") (10 10619.3438914027
6719.4570135747 0.0) (11 10617.2087104072 6717.7488687783 0.0))
((0 . "LINE") (100 . "AcDbEntity") (8 . "ARCH") (62 . 7) (370 . 13) (100 . "AcDbLine") (10 10617.2087104072
6717.7488687783 0.0) (11 10579.9632352941 6687.9524886878 0.0))
((0 . "LINE") (100 . "AcDbEntity") (8 . "ARCH") (62 . 7) (370 . 13) (100 . "AcDbLine") (10 10579.9632352941
6687.9524886878 0.0) (11 10576.9230769231 6685.520361991 0.0))
((0 . "LINE") (100 . "AcDbEntity") (8 . "ARCH") (62 . 7) (370 . 13) (100 . "AcDbLine") (10 10576.9230769231
6685.520361991 0.0) (11 10541.556561086 6641.3122171946 0.0))
((0 . "LINE") (100 . "AcDbEntity") (8 . "ARCH") (62 . 7) (370 . 13) (100 . "AcDbLine") (10 10541.556561086
6641.3122171946 0.0) (11 10540.7239819005 6640.2714932127 0.0))
((0 . "LINE") (100 . "AcDbEntity") (8 . "ARCH") (62 . 7) (370 . 13) (100 . "AcDbLine") (10 10540.7239819005
6640.2714932127 0.0) (11 10531.6742081448 6628.9592760181 0.0))
((0 . "LINE") (100 . "AcDbEntity") (8 . "ARCH") (62 . 7) (370 . 13) (100 . "AcDbLine") (10 10531.6742081448
6628.9592760181 0.0) (11 10531.6742081448 6607.0701357466 0.0))
((0 . "LINE") (100 . "AcDbEntity") (8 . "ARCH") (62 . 7) (370 . 13) (100 . "AcDbLine") (10 10531.6742081448
6607.0701357466 0.0) (11 10531.6742081448 6549.7737556561 0.0))
((0 . "LINE") (100 . "AcDbEntity") (8 . "ARCH") (62 . 7) (370 . 13) (100 . "AcDbLine") (10 10531.6742081448
6549.7737556561 0.0) (11 10531.6742081448 6470.5882352941 0.0))
((0 . "LINE") (100 . "AcDbEntity") (8 . "ARCH") (62 . 7) (370 . 13) (100 . "AcDbLine") (10 10531.6742081448
6470.5882352941 0.0) (11 10531.6742081448 6436.6515837104 0.0))
((0 . "LINE") (100 . "AcDbEntity") (8 . "ARCH") (62 . 7) (370 . 13) (100 . "AcDbLine") (10 10531.6742081448
6436.6515837104 0.0) (11 9479.6380090498 6436.6515837104 0.0))
((0 . "LINE") (100 . "AcDbEntity") (8 . "ARCH") (62 . 7) (370 . 13) (100 . "AcDbLine") (10 9479.6380090498
6436.6515837104 0.0) (11 9479.6380090498 6470.5882352941 0.0))
((0 . "LINE") (100 . "AcDbEntity") (8 . "ARCH") (62 . 7) (370 . 13) (100 . "AcDbLine") (10 9479.6380090498
6470.5882352941 0.0) (11 9479.6380090498 6549.7737556561 0.0))
((0 . "LINE") (100 . "AcDbEntity") (8 . "ARCH") (62 . 7) (370 . 13) (100 . "AcDbLine") (10 9479.6380090498
6549.7737556561 0.0) (11 9479.6380090498 6607.2624434389 0.0))
((0 . "LINE") (100 . "AcDbEntity") (8 . "ARCH") (62 . 7) (370 . 13) (100 . "AcDbLine") (10 9479.6380090498
6607.2624434389 0.0) (11 9479.6380090498 6628.9592760181 0.0))
((0 . "LINE") (100 . "AcDbEntity") (8 . "ARCH") (62 . 7) (370 . 13) (100 . "AcDbLine") (10 9479.6380090498
6628.9592760181 0.0) (11 9470.5882352941 6640.2714932127 0.0))
((0 . "LINE") (100 . "AcDbEntity") (8 . "ARCH") (62 . 7) (370 . 13) (100 . "AcDbLine") (10 9470.5882352941
6640.2714932127 0.0) (11 9468.3257918552 6643.0995475113 0.0))
((0 . "LINE") (100 . "AcDbEntity") (8 . "ARCH") (62 . 7) (370 . 13) (100 . "AcDbLine") (10 9468.3257918552
6643.0995475113 0.0) (11 9434.3891402715 6685.520361991 0.0))
((0 . "LINE") (100 . "AcDbEntity") (8 . "ARCH") (62 . 7) (370 . 13) (100 . "AcDbLine") (10 9434.3891402715
6685.520361991 0.0) (11 9402.9411764706 6710.6787330317 0.0))
((0 . "LINE") (100 . "AcDbEntity") (8 . "ARCH") (62 . 7) (370 . 13) (100 . "AcDbLine") (10 9402.9411764706
6710.6787330317 0.0) (11 9391.9683257919 6719.4570135747 0.0))
((0 . "LINE") (100 . "AcDbEntity") (8 . "ARCH") (62 . 7) (370 . 13) (100 . "AcDbLine") (10 9391.9683257919
6719.4570135747 0.0) (11 9377.8280542986 6730.7692307692 0.0))
((0 . "LINE") (100 . "AcDbEntity") (8 . "ARCH") (62 . 7) (370 . 13) (100 . "AcDbLine") (10 9377.8280542986
6730.7692307692 0.0) (11 9377.8280542986 6762.4547511312 0.0))
((0 . "LINE") (100 . "AcDbEntity") (8 . "ARCH") (62 . 7) (370 . 13) (100 . "AcDbLine") (10 9377.8280542986
6762.4547511312 0.0) (11 9377.8280542986 6809.9547511312 0.0))
((0 . "LINE") (100 . "AcDbEntity") (8 . "ARCH") (62 . 7) (370 . 13) (100 . "AcDbLine") (10 9389.1402714932
6719.4570135747 0.0) (11 9391.9683257919 6719.4570135747 0.0))
((0 . "LINE") (100 . "AcDbEntity") (8 . "ARCH") (62 . 7) (370 . 13) (100 . "AcDbLine") (10 9391.9683257919
6719.4570135747 0.0) (11 10619.3438914027 6719.4570135747 0.0))
((0 . "LINE") (100 . "AcDbEntity") (8 . "ARCH") (62 . 7) (370 . 13) (100 . "AcDbLine") (10 10619.3438914027
6719.4570135747 0.0) (11 10622.1719457014 6719.4570135747 0.0))
((0 . "LINE") (100 . "AcDbEntity") (8 . "ARCH") (62 . 7) (370 . 13) (100 . "AcDbLine") (10 9468.3257918552
6640.2714932127 0.0) (11 9470.5882352941 6640.2714932127 0.0))
((0 . "LINE") (100 . "AcDbEntity") (8 . "ARCH") (62 . 7) (370 . 13) (100 . "AcDbLine") (10 9470.5882352941
6640.2714932127 0.0) (11 10540.7239819005 6640.2714932127 0.0))
((0 . "LINE") (100 . "AcDbEntity") (8 . "ARCH") (62 . 7) (370 . 13) (100 . "AcDbLine") (10 10540.7239819005
6640.2714932127 0.0) (11 10542.9864253394 6640.2714932127 0.0))
((0 . "LINE") (100 . "AcDbEntity") (8 . "ARCH") (62 . 7) (370 . 13) (100 . "AcDbLine") (10 7929.8642533937
6199.0950226244 0.0) (11 9547.5113122172 6199.0950226244 0.0))
((0 . "LINE") (100 . "AcDbEntity") (8 . "ARCH") (62 . 7) (370 . 13) (100 . "AcDbLine") (10 7929.8642533937
5814.4796380091 0.0) (11 9547.5113122172 5814.4796380091 0.0))
((0 . "LINE") (100 . "AcDbEntity") (8 . "ARCH") (62 . 7) (370 . 13) (100 . "AcDbLine") (10 7929.8642533937
5735.2941176471 0.0) (11 9547.5113122172 5735.2941176471 0.0))
((0 . "LINE") (100 . "AcDbEntity") (8 . "ARCH") (62 . 7) (370 . 13) (100 . "AcDbLine") (10 7929.8642533937
5599.5475113122 0.0) (11 9547.5113122172 5599.5475113122 0.0))
((0 . "LINE") (100 . "AcDbEntity") (8 . "ARCH") (62 . 7) (370 . 13) (100 . "AcDbLine") (10 7929.8642533937
2816.742081448 0.0) (11 9547.5113122172 2816.742081448 0.0))
((0 . "LINE") (100 . "AcDbEntity") (8 . "ARCH") (62 . 7) (370 . 13) (100 . "AcDbLine") (10 7929.8642533937
2703.6199095023 0.0) (11 9547.5113122172 2703.6199095023 0.0))
((0 . "LINE") (100 . "AcDbEntity") (8 . "ARCH") (62 . 7) (370 . 13) (100 . "AcDbLine") (10 7929.8642533937
4909.5022624434 0.0) (11 8212.6696832579 4909.5022624434 0.0))
((0 . "LINE") (100 . "AcDbEntity") (8 . "ARCH") (62 . 7) (370 . 13) (100 . "AcDbLine") (10 9298.6425339367
4909.5022624434 0.0) (11 9547.5113122172 4909.5022624434 0.0))
((0 . "LINE") (100 . "AcDbEntity") (8 . "ARCH") (62 . 7) (370 . 13) (100 . "AcDbLine") (10 10452.4886877828
6199.0950226244 0.0) (11 12036.1990950226 6199.0950226244 0.0))
((0 . "LINE") (100 . "AcDbEntity") (8 . "ARCH") (62 . 7) (370 . 13) (100 . "AcDbLine") (10 10452.4886877828
5814.4796380091 0.0) (11 12036.1990950226 5814.4796380091 0.0))
((0 . "LINE") (100 . "AcDbEntity") (8 . "ARCH") (62 . 7) (370 . 13) (100 . "AcDbLine") (10 10452.4886877828
5735.2941176471 0.0) (11 12036.1990950226 5735.2941176471 0.0))
((0 . "LINE") (100 . "AcDbEntity") (8 . "ARCH") (62 . 7) (370 . 13) (100 . "AcDbLine") (10 10452.4886877828
5599.5475113122 0.0) (11 12036.1990950226 5599.5475113122 0.0))
((0 . "LINE") (100 . "AcDbEntity") (8 . "ARCH") (62 . 7) (370 . 13) (100 . "AcDbLine") (10 10452.4886877828
2816.742081448 0.0) (11 12036.1990950226 2816.742081448 0.0))
((0 . "LINE") (100 . "AcDbEntity") (8 . "ARCH") (62 . 7) (370 . 13) (100 . "AcDbLine") (10 10452.4886877828
2703.6199095023 0.0) (11 12036.1990950226 2703.6199095023 0.0))
((0 . "LINE") (100 . "AcDbEntity") (8 . "ARCH") (62 . 7) (370 . 13) (100 . "AcDbLine") (10 10452.4886877828
4909.5022624434 0.0) (11 10712.6696832579 4909.5022624434 0.0))
((0 . "LINE") (100 . "AcDbEntity") (8 . "ARCH") (62 . 7) (370 . 13) (100 . "AcDbLine") (10 11798.6425339367
4909.5022624434 0.0) (11 12036.1990950226 4909.5022624434 0.0))
((0 . "LINE") (100 . "AcDbEntity") (8 . "ARCH") (62 . 7) (370 . 13) (100 . "AcDbLine") (10 7952.4886877828
6549.7737556561 0.0) (11 8009.0497737557 6549.7737556561 0.0))
((0 . "LINE") (100 . "AcDbEntity") (8 . "ARCH") (62 . 7) (370 . 13) (100 . "AcDbLine") (10 8009.0497737557
6549.7737556561 0.0) (11 8597.2850678733 6549.7737556561 0.0))
((0 . "LINE") (100 . "AcDbEntity") (8 . "ARCH") (62 . 7) (370 . 13) (100 . "AcDbLine") (10 8597.2850678733
6549.7737556561 0.0) (11 8597.2850678733 6391.4027149321 0.0))
((0 . "LINE") (100 . "AcDbEntity") (8 . "ARCH") (62 . 7) (370 . 13) (100 . "AcDbLine") (10 8597.2850678733
6391.4027149321 0.0) (11 8766.9683257919 6391.4027149321 0.0))
((0 . "LINE") (100 . "AcDbEntity") (8 . "ARCH") (62 . 7) (370 . 13) (100 . "AcDbLine") (10 8766.9683257919
6391.4027149321 0.0) (11 8766.9683257919 6549.7737556561 0.0))
((0 . "LINE") (100 . "AcDbEntity") (8 . "ARCH") (62 . 7) (370 . 13) (100 . "AcDbLine") (10 8766.9683257919
6549.7737556561 0.0) (11 8947.963800905 6549.7737556561 0.0))
((0 . "LINE") (100 . "AcDbEntity") (8 . "ARCH") (62 . 7) (370 . 13) (100 . "AcDbLine") (10 8947.963800905
6549.7737556561 0.0) (11 9004.5248868778 6549.7737556561 0.0))
((0 . "LINE") (100 . "AcDbEntity") (8 . "ARCH") (62 . 7) (370 . 13) (100 . "AcDbLine") (10 9004.5248868778
6549.7737556561 0.0) (11 9106.334841629 6549.7737556561 0.0))
((0 . "LINE") (100 . "AcDbEntity") (8 . "ARCH") (62 . 7) (370 . 13) (100 . "AcDbLine") (10 9106.334841629
6549.7737556561 0.0) (11 9479.6380090498 6549.7737556561 0.0))
((0 . "LINE") (100 . "AcDbEntity") (8 . "ARCH") (62 . 7) (370 . 13) (100 . "AcDbLine") (10 7929.8642533937
6470.5882352941 0.0) (11 8529.4117647059 6470.5882352941 0.0))
((0 . "LINE") (100 . "AcDbEntity") (8 . "ARCH") (62 . 7) (370 . 13) (100 . "AcDbLine") (10 8529.4117647059
6470.5882352941 0.0) (11 8529.4117647059 6334.8416289593 0.0))
((0 . "LINE") (100 . "AcDbEntity") (8 . "ARCH") (62 . 7) (370 . 13) (100 . "AcDbLine") (10 8529.4117647059
6334.8416289593 0.0) (11 8834.8416289593 6334.8416289593 0.0))
((0 . "LINE") (100 . "AcDbEntity") (8 . "ARCH") (62 . 7) (370 . 13) (100 . "AcDbLine") (10 8834.8416289593
6334.8416289593 0.0) (11 8834.8416289593 6470.5882352941 0.0))
((0 . "LINE") (100 . "AcDbEntity") (8 . "ARCH") (62 . 7) (370 . 13) (100 . "AcDbLine") (10 8834.8416289593
6470.5882352941 0.0) (11 9479.6380090498 6470.5882352941 0.0))
((0 . "LINE") (100 . "AcDbEntity") (8 . "ARCH") (62 . 7) (370 . 13) (100 . "AcDbLine") (10 10531.6742081448
6549.7737556561 0.0) (11 10927.6018099548 6549.7737556561 0.0))
((0 . "LINE") (100 . "AcDbEntity") (8 . "ARCH") (62 . 7) (370 . 13) (100 . "AcDbLine") (10 10927.6018099548
6549.7737556561 0.0) (11 11029.4117647059 6549.7737556561 0.0))
((0 . "LINE") (100 . "AcDbEntity") (8 . "ARCH") (62 . 7) (370 . 13) (100 . "AcDbLine") (10 11029.4117647059
6549.7737556561 0.0) (11 11085.9728506787 6549.7737556561 0.0))
((0 . "LINE") (100 . "AcDbEntity") (8 . "ARCH") (62 . 7) (370 . 13) (100 . "AcDbLine") (10 11085.9728506787
6549.7737556561 0.0) (11 11142.5339366516 6549.7737556561 0.0))
((0 . "LINE") (100 . "AcDbEntity") (8 . "ARCH") (62 . 7) (370 . 13) (100 . "AcDbLine") (10 11142.5339366516
6549.7737556561 0.0) (11 11142.5339366516 6391.4027149321 0.0))
((0 . "LINE") (100 . "AcDbEntity") (8 . "ARCH") (62 . 7) (370 . 13) (100 . "AcDbLine") (10 11142.5339366516
6391.4027149321 0.0) (11 11323.5294117647 6391.4027149321 0.0))
((0 . "LINE") (100 . "AcDbEntity") (8 . "ARCH") (62 . 7) (370 . 13) (100 . "AcDbLine") (10 11323.5294117647
6391.4027149321 0.0) (11 11323.5294117647 6549.7737556561 0.0))
((0 . "LINE") (100 . "AcDbEntity") (8 . "ARCH") (62 . 7) (370 . 13) (100 . "AcDbLine") (10 11323.5294117647
6549.7737556561 0.0) (11 11979.6380090498 6549.7737556561 0.0))
((0 . "LINE") (100 . "AcDbEntity") (8 . "ARCH") (62 . 7) (370 . 13) (100 . "AcDbLine") (10 11979.6380090498
6549.7737556561 0.0) (11 12036.1990950226 6549.7737556561 0.0))
((0 . "LINE") (100 . "AcDbEntity") (8 . "ARCH") (62 . 7) (370 . 13) (100 . "AcDbLine") (10 10531.6742081448
6470.5882352941 0.0) (11 11074.6606334842 6470.5882352941 0.0))
((0 . "LINE") (100 . "AcDbEntity") (8 . "ARCH") (62 . 7) (370 . 13) (100 . "AcDbLine") (10 11074.6606334842
6470.5882352941 0.0) (11 11074.6606334842 6334.8416289593 0.0))
((0 . "LINE") (100 . "AcDbEntity") (8 . "ARCH") (62 . 7) (370 . 13) (100 . "AcDbLine") (10 11074.6606334842
6334.8416289593 0.0) (11 11391.4027149321 6334.8416289593 0.0))
((0 . "LINE") (100 . "AcDbEntity") (8 . "ARCH") (62 . 7) (370 . 13) (100 . "AcDbLine") (10 11391.4027149321
6334.8416289593 0.0) (11 11391.4027149321 6470.5882352941 0.0))
((0 . "LINE") (100 . "AcDbEntity") (8 . "ARCH") (62 . 7) (370 . 13) (100 . "AcDbLine") (10 11391.4027149321
6470.5882352941 0.0) (11 12036.1990950226 6470.5882352941 0.0))
((0 . "LINE") (100 . "AcDbEntity") (8 . "ARCH") (62 . 7) (370 . 13) (100 . "AcDbLine") (10 4276.0180995475
6549.7737556561 0.0) (11 4309.9547511312 6549.7737556561 0.0))
((0 . "LINE") (100 . "AcDbEntity") (8 . "ARCH") (62 . 7) (370 . 13) (100 . "AcDbLine") (10 4309.9547511312
6549.7737556561 0.0) (11 4434.3891402715 6549.7737556561 0.0))
((0 . "LINE") (100 . "AcDbEntity") (8 . "ARCH") (62 . 7) (370 . 13) (100 . "AcDbLine") (10 4434.3891402715
6549.7737556561 0.0) (11 4490.9502262443 6549.7737556561 0.0))
((0 . "LINE") (100 . "AcDbEntity") (8 . "ARCH") (62 . 7) (370 . 13) (100 . "AcDbLine") (10 4490.9502262443
6549.7737556561 0.0) (11 6572.3981900452 6549.7737556561 0.0))
((0 . "LINE") (100 . "AcDbEntity") (8 . "ARCH") (62 . 7) (370 . 13) (100 . "AcDbLine") (10 6572.3981900452
6549.7737556561 0.0) (11 6628.9592760181 6549.7737556561 0.0))
((0 . "LINE") (100 . "AcDbEntity") (8 . "ARCH") (62 . 7) (370 . 13) (100 . "AcDbLine") (10 4276.0180995475
6470.5882352941 0.0) (11 6628.9592760181 6470.5882352941 0.0))
((0 . "LINE") (100 . "AcDbEntity") (8 . "ARCH") (62 . 7) (370 . 13) (100 . "AcDbLine") (10 4276.0180995475
6199.0950226244 0.0) (11 6628.9592760181 6199.0950226244 0.0))
((0 . "LINE") (100 . "AcDbEntity") (8 . "ARCH") (62 . 7) (370 . 13) (100 . "AcDbLine") (10 13348.4162895928
6549.7737556561 0.0) (11 13438.9140271493 6549.7737556561 0.0))
((0 . "LINE") (100 . "AcDbEntity") (8 . "ARCH") (62 . 7) (370 . 13) (100 . "AcDbLine") (10 13438.9140271493
6549.7737556561 0.0) (11 15554.2986425339 6549.7737556561 0.0))
((0 . "LINE") (100 . "AcDbEntity") (8 . "ARCH") (62 . 7) (370 . 13) (100 . "AcDbLine") (10 15554.2986425339
6549.7737556561 0.0) (11 15610.8597285068 6549.7737556561 0.0))
((0 . "LINE") (100 . "AcDbEntity") (8 . "ARCH") (62 . 7) (370 . 13) (100 . "AcDbLine") (10 15610.8597285068
6549.7737556561 0.0) (11 15712.6696832579 6549.7737556561 0.0))
((0 . "LINE") (100 . "AcDbEntity") (8 . "ARCH") (62 . 7) (370 . 13) (100 . "AcDbLine") (10 15712.6696832579
6549.7737556561 0.0) (11 15769.2307692308 6549.7737556561 0.0))
((0 . "LINE") (100 . "AcDbEntity") (8 . "ARCH") (62 . 7) (370 . 13) (100 . "AcDbLine") (10 13348.4162895928
6470.5882352941 0.0) (11 15769.2307692308 6470.5882352941 0.0))
((0 . "LINE") (100 . "AcDbEntity") (8 . "ARCH") (62 . 7) (370 . 13) (100 . "AcDbLine") (10 13348.4162895928
6199.0950226244 0.0) (11 15769.2307692308 6199.0950226244 0.0))
((0 . "LINE") (100 . "AcDbEntity") (8 . "ARCH") (62 . 7) (370 . 13) (100 . "AcDbLine") (10 4276.0180995475
6730.7692307692 0.0) (11 4276.0180995475 6549.7737556561 0.0))
((0 . "LINE") (100 . "AcDbEntity") (8 . "ARCH") (62 . 7) (370 . 13) (100 . "AcDbLine") (10 4276.0180995475
6549.7737556561 0.0) (11 4276.0180995475 6481.9004524887 0.0))
((0 . "LINE") (100 . "AcDbEntity") (8 . "ARCH") (62 . 7) (370 . 13) (100 . "AcDbLine") (10 4276.0180995475
6481.9004524887 0.0) (11 4000.4985067873 6481.9004524887 0.0))
((0 . "LINE") (100 . "AcDbEntity") (8 . "ARCH") (62 . 7) (370 . 13) (100 . "AcDbLine") (10 3804.9313574661
6481.9004524887 0.0) (11 3264.0539932127 6481.9004524887 0.0))
((0 . "LINE") (100 . "AcDbEntity") (8 . "ARCH") (62 . 7) (370 . 13) (100 . "AcDbLine") (10 3070.7876357466
6481.9004524887 0.0) (11 2782.8054298643 6481.9004524887 0.0))
((0 . "LINE") (100 . "AcDbEntity") (8 . "ARCH") (62 . 7) (370 . 13) (100 . "AcDbLine") (10 2782.8054298643
6481.9004524887 0.0) (11 2782.8054298643 6549.7737556561 0.0))
((0 . "LINE") (100 . "AcDbEntity") (8 . "ARCH") (62 . 7) (370 . 13) (100 . "AcDbLine") (10 2782.8054298643
6549.7737556561 0.0) (11 2782.8054298643 6730.7692307692 0.0))
((0 . "LINE") (100 . "AcDbEntity") (8 . "ARCH") (62 . 7) (370 . 13) (100 . "AcDbLine") (10 7941.1764705882
6730.7692307692 0.0) (11 7941.1764705882 6481.9004524887 0.0))
((0 . "LINE") (100 . "AcDbEntity") (8 . "ARCH") (62 . 7) (370 . 13) (100 . "AcDbLine") (10 7941.1764705882
6481.9004524887 0.0) (11 7929.8642533937 6481.9004524887 0.0))
((0 . "LINE") (100 . "AcDbEntity") (8 . "ARCH") (62 . 7) (370 . 13) (100 . "AcDbLine") (10 7929.8642533937
6481.9004524887 0.0) (11 7766.3673642534 6481.9004524887 0.0))
((0 . "LINE") (100 . "AcDbEntity") (8 . "ARCH") (62 . 7) (370 . 13) (100 . "AcDbLine") (10 7550.3747171946
6481.9004524887 0.0) (11 7044.7296153846 6481.9004524887 0.0))
((0 . "LINE") (100 . "AcDbEntity") (8 . "ARCH") (62 . 7) (370 . 13) (100 . "AcDbLine") (10 6846.6730995475
6481.9004524887 0.0) (11 6628.9592760181 6481.9004524887 0.0))
((0 . "LINE") (100 . "AcDbEntity") (8 . "ARCH") (62 . 7) (370 . 13) (100 . "AcDbLine") (10 6628.9592760181
6481.9004524887 0.0) (11 6628.9592760181 6549.7737556561 0.0))
((0 . "LINE") (100 . "AcDbEntity") (8 . "ARCH") (62 . 7) (370 . 13) (100 . "AcDbLine") (10 6628.9592760181
6549.7737556561 0.0) (11 6628.9592760181 6730.7692307692 0.0))
((0 . "LINE") (100 . "AcDbEntity") (8 . "ARCH") (62 . 7) (370 . 13) (100 . "AcDbLine") (10 13348.4162895928
6730.7692307692 0.0) (11 13348.4162895928 6549.7737556561 0.0))
((0 . "LINE") (100 . "AcDbEntity") (8 . "ARCH") (62 . 7) (370 . 13) (100 . "AcDbLine") (10 13348.4162895928
6549.7737556561 0.0) (11 13348.4162895928 6481.9004524887 0.0))
((0 . "LINE") (100 . "AcDbEntity") (8 . "ARCH") (62 . 7) (370 . 13) (100 . "AcDbLine") (10 13348.4162895928
6481.9004524887 0.0) (11 13156.6848755656 6481.9004524887 0.0))
((0 . "LINE") (100 . "AcDbEntity") (8 . "ARCH") (62 . 7) (370 . 13) (100 . "AcDbLine") (10 12951.9124095023
6481.9004524887 0.0) (11 12481.146300905 6481.9004524887 0.0))
((0 . "LINE") (100 . "AcDbEntity") (8 . "ARCH") (62 . 7) (370 . 13) (100 . "AcDbLine") (10 12247.3604864253
6481.9004524887 0.0) (11 12036.1990950226 6481.9004524887 0.0))
((0 . "LINE") (100 . "AcDbEntity") (8 . "ARCH") (62 . 7) (370 . 13) (100 . "AcDbLine") (10 12036.1990950226
6481.9004524887 0.0) (11 12036.1990950226 6549.7737556561 0.0))
((0 . "LINE") (100 . "AcDbEntity") (8 . "ARCH") (62 . 7) (370 . 13) (100 . "AcDbLine") (10 12036.1990950226
6549.7737556561 0.0) (11 12036.1990950226 6730.7692307692 0.0))
((0 . "LINE") (100 . "AcDbEntity") (8 . "ARCH") (62 . 7) (370 . 13) (100 . "AcDbLine") (10 17239.8190045249
6730.7692307692 0.0) (11 17239.8190045249 6549.7737556561 0.0))
((0 . "LINE") (100 . "AcDbEntity") (8 . "ARCH") (62 . 7) (370 . 13) (100 . "AcDbLine") (10 17239.8190045249
6549.7737556561 0.0) (11 17239.8190045249 6481.9004524887 0.0))
((0 . "LINE") (100 . "AcDbEntity") (8 . "ARCH") (62 . 7) (370 . 13) (100 . "AcDbLine") (10 17239.8190045249
6481.9004524887 0.0) (11 17017.9934954751 6481.9004524887 0.0))
((0 . "LINE") (100 . "AcDbEntity") (8 . "ARCH") (62 . 7) (370 . 13) (100 . "AcDbLine") (10 16782.9114819005
6481.9004524887 0.0) (11 16226.4003733032 6481.9004524887 0.0))
((0 . "LINE") (100 . "AcDbEntity") (8 . "ARCH") (62 . 7) (370 . 13) (100 . "AcDbLine") (10 16013.4186312217
6481.9004524887 0.0) (11 15769.2307692308 6481.9004524887 0.0))
((0 . "LINE") (100 . "AcDbEntity") (8 . "ARCH") (62 . 7) (370 . 13) (100 . "AcDbLine") (10 15769.2307692308
6481.9004524887 0.0) (11 15769.2307692308 6549.7737556561 0.0))
((0 . "LINE") (100 . "AcDbEntity") (8 . "ARCH") (62 . 7) (370 . 13) (100 . "AcDbLine") (10 15769.2307692308
6549.7737556561 0.0) (11 15769.2307692308 6730.7692307692 0.0))
((0 . "LINE") (100 . "AcDbEntity") (8 . "ARCH") (62 . 7) (370 . 13) (100 . "AcDbLine") (10 2952.4886877828
7952.4886877828 0.0) (11 3710.407239819 7952.4886877828 0.0))
((0 . "LINE") (100 . "AcDbEntity") (8 . "ARCH") (62 . 7) (370 . 13) (100 . "AcDbLine") (10 3710.407239819
7952.4886877828 0.0) (11 3710.407239819 7828.0542986425 0.0))
((0 . "LINE") (100 . "AcDbEntity") (8 . "ARCH") (62 . 7) (370 . 13) (100 . "AcDbLine") (10 3710.407239819
7828.0542986425 0.0) (11 3710.407239819 7760.1809954751 0.0))
((0 . "LINE") (100 . "AcDbEntity") (8 . "ARCH") (62 . 7) (370 . 13) (100 . "AcDbLine") (10 3710.407239819
7760.1809954751 0.0) (11 3710.407239819 7635.7466063348 0.0))
((0 . "LINE") (100 . "AcDbEntity") (8 . "ARCH") (62 . 7) (370 . 13) (100 . "AcDbLine") (10 3710.407239819
7635.7466063348 0.0) (11 2952.4886877828 7635.7466063348 0.0))
((0 . "LINE") (100 . "AcDbEntity") (8 . "ARCH") (62 . 7) (370 . 13) (100 . "AcDbLine") (10 2952.4886877828
7635.7466063348 0.0) (11 2952.4886877828 7952.4886877828 0.0))
((0 . "LINE") (100 . "AcDbEntity") (8 . "ARCH") (62 . 7) (370 . 13) (100 . "AcDbLine") (10 2952.4886877828
7601.8099547511 0.0) (11 3710.407239819 7601.8099547511 0.0))
((0 . "LINE") (100 . "AcDbEntity") (8 . "ARCH") (62 . 7) (370 . 13) (100 . "AcDbLine") (10 2952.4886877828
7635.7466063348 0.0) (11 2952.4886877828 7601.8099547511 0.0))
((0 . "LINE") (100 . "AcDbEntity") (8 . "ARCH") (62 . 7) (370 . 13) (100 . "AcDbLine") (10 2952.4886877828
7601.8099547511 0.0) (11 2952.4886877828 7165.5518438914 0.0))
((0 . "LINE") (100 . "AcDbEntity") (8 . "ARCH") (62 . 7) (370 . 13) (100 . "AcDbLine") (10 3710.407239819
7635.7466063348 0.0) (11 3710.407239819 7601.8099547511 0.0))
((0 . "LINE") (100 . "AcDbEntity") (8 . "ARCH") (62 . 7) (370 . 13) (100 . "AcDbLine") (10 3710.407239819
7601.8099547511 0.0) (11 3710.407239819 7567.8733031674 0.0))
((0 . "LINE") (100 . "AcDbEntity") (8 . "ARCH") (62 . 7) (370 . 13) (100 . "AcDbLine") (10 3710.407239819
7567.8733031674 0.0) (11 3710.407239819 7160.4200452489 0.0))
((0 . "LINE") (100 . "AcDbEntity") (8 . "ARCH") (62 . 7) (370 . 13) (100 . "AcDbLine") (10 2895.92760181 8178.7330316742
0.0) (11 3789.592760181 8178.7330316742 0.0))
((0 . "LINE") (100 . "AcDbEntity") (8 . "ARCH") (62 . 7) (370 . 13) (100 . "AcDbLine") (10 3789.592760181
8178.7330316742 0.0) (11 3789.592760181 8076.9230769231 0.0))
((0 . "LINE") (100 . "AcDbEntity") (8 . "ARCH") (62 . 7) (370 . 13) (100 . "AcDbLine") (10 3789.592760181
8076.9230769231 0.0) (11 3755.6561085973 8076.9230769231 0.0))
((0 . "LINE") (100 . "AcDbEntity") (8 . "ARCH") (62 . 7) (370 . 13) (100 . "AcDbLine") (10 3755.6561085973
8076.9230769231 0.0) (11 3753.3936651584 8065.6108597285 0.0))
((0 . "LINE") (100 . "AcDbEntity") (8 . "ARCH") (62 . 7) (370 . 13) (100 . "AcDbLine") (10 3753.3936651584
8065.6108597285 0.0) (11 3744.3438914027 8020.3619909502 0.0))
((0 . "LINE") (100 . "AcDbEntity") (8 . "ARCH") (62 . 7) (370 . 13) (100 . "AcDbLine") (10 3744.3438914027
8020.3619909502 0.0) (11 3730.7692307692 7997.7375565611 0.0))
((0 . "LINE") (100 . "AcDbEntity") (8 . "ARCH") (62 . 7) (370 . 13) (100 . "AcDbLine") (10 3730.7692307692
7997.7375565611 0.0) (11 3710.407239819 7963.8009049774 0.0))
((0 . "LINE") (100 . "AcDbEntity") (8 . "ARCH") (62 . 7) (370 . 13) (100 . "AcDbLine") (10 3710.407239819
7963.8009049774 0.0) (11 2952.4886877828 7963.8009049774 0.0))
((0 . "LINE") (100 . "AcDbEntity") (8 . "ARCH") (62 . 7) (370 . 13) (100 . "AcDbLine") (10 2952.4886877828
7963.8009049774 0.0) (11 2938.9140271493 7997.7375565611 0.0))
((0 . "LINE") (100 . "AcDbEntity") (8 . "ARCH") (62 . 7) (370 . 13) (100 . "AcDbLine") (10 2938.9140271493
7997.7375565611 0.0) (11 2929.8642533937 8020.3619909502 0.0))
((0 . "LINE") (100 . "AcDbEntity") (8 . "ARCH") (62 . 7) (370 . 13) (100 . "AcDbLine") (10 2929.8642533937
8020.3619909502 0.0) (11 2907.2398190045 8065.6108597285 0.0))
((0 . "LINE") (100 . "AcDbEntity") (8 . "ARCH") (62 . 7) (370 . 13) (100 . "AcDbLine") (10 2907.2398190045
8065.6108597285 0.0) (11 2895.92760181 8065.6108597285 0.0))
((0 . "LINE") (100 . "AcDbEntity") (8 . "ARCH") (62 . 7) (370 . 13) (100 . "AcDbLine") (10 2895.92760181 8065.6108597285
0.0) (11 2895.92760181 8178.7330316742 0.0))
((0 . "LINE") (100 . "AcDbEntity") (8 . "ARCH") (62 . 7) (370 . 13) (100 . "AcDbLine") (10 2907.2398190045
8065.6108597285 0.0) (11 3753.3936651584 8065.6108597285 0.0))
((0 . "LINE") (100 . "AcDbEntity") (8 . "ARCH") (62 . 7) (370 . 13) (100 . "AcDbLine") (10 3753.3936651584
8065.6108597285 0.0) (11 3778.2805429864 8065.6108597285 0.0))
((0 . "LINE") (100 . "AcDbEntity") (8 . "ARCH") (62 . 7) (370 . 13) (100 . "AcDbLine") (10 2938.9140271493
7997.7375565611 0.0) (11 3730.7692307692 7997.7375565611 0.0))
((0 . "LINE") (100 . "AcDbEntity") (8 . "ARCH") (62 . 7) (370 . 13) (100 . "AcDbLine") (10 16334.8416289593
7952.4886877828 0.0) (11 17092.7601809955 7952.4886877828 0.0))
((0 . "LINE") (100 . "AcDbEntity") (8 . "ARCH") (62 . 7) (370 . 13) (100 . "AcDbLine") (10 17092.7601809955
7952.4886877828 0.0) (11 17092.7601809955 7635.7466063348 0.0))
((0 . "LINE") (100 . "AcDbEntity") (8 . "ARCH") (62 . 7) (370 . 13) (100 . "AcDbLine") (10 17092.7601809955
7635.7466063348 0.0) (11 16334.8416289593 7635.7466063348 0.0))
((0 . "LINE") (100 . "AcDbEntity") (8 . "ARCH") (62 . 7) (370 . 13) (100 . "AcDbLine") (10 16334.8416289593
7635.7466063348 0.0) (11 16334.8416289593 7760.1809954751 0.0))
((0 . "LINE") (100 . "AcDbEntity") (8 . "ARCH") (62 . 7) (370 . 13) (100 . "AcDbLine") (10 16334.8416289593
7760.1809954751 0.0) (11 16334.8416289593 7828.0542986425 0.0))
((0 . "LINE") (100 . "AcDbEntity") (8 . "ARCH") (62 . 7) (370 . 13) (100 . "AcDbLine") (10 16334.8416289593
7828.0542986425 0.0) (11 16334.8416289593 7952.4886877828 0.0))
((0 . "LINE") (100 . "AcDbEntity") (8 . "ARCH") (62 . 7) (370 . 13) (100 . "AcDbLine") (10 16334.8416289593
7601.8099547511 0.0) (11 17092.7601809955 7601.8099547511 0.0))
((0 . "LINE") (100 . "AcDbEntity") (8 . "ARCH") (62 . 7) (370 . 13) (100 . "AcDbLine") (10 16334.8416289593
7635.7466063348 0.0) (11 16334.8416289593 7601.8099547511 0.0))
((0 . "LINE") (100 . "AcDbEntity") (8 . "ARCH") (62 . 7) (370 . 13) (100 . "AcDbLine") (10 16334.8416289593
7601.8099547511 0.0) (11 16334.8416289593 7567.8733031674 0.0))
((0 . "LINE") (100 . "AcDbEntity") (8 . "ARCH") (62 . 7) (370 . 13) (100 . "AcDbLine") (10 16334.8416289593
7567.8733031674 0.0) (11 16334.8416289593 7085.0678733032 0.0))
((0 . "LINE") (100 . "AcDbEntity") (8 . "ARCH") (62 . 7) (370 . 13) (100 . "AcDbLine") (10 17092.7601809955
7635.7466063348 0.0) (11 17092.7601809955 7601.8099547511 0.0))
((0 . "LINE") (100 . "AcDbEntity") (8 . "ARCH") (62 . 7) (370 . 13) (100 . "AcDbLine") (10 17092.7601809955
7601.8099547511 0.0) (11 17092.7601809955 7118.8811199095 0.0))
((0 . "LINE") (100 . "AcDbEntity") (8 . "ARCH") (62 . 7) (370 . 13) (100 . "AcDbLine") (10 16278.2805429864
8178.7330316742 0.0) (11 17171.9457013575 8178.7330316742 0.0))
((0 . "LINE") (100 . "AcDbEntity") (8 . "ARCH") (62 . 7) (370 . 13) (100 . "AcDbLine") (10 17171.9457013575
8178.7330316742 0.0) (11 17171.9457013575 8076.9230769231 0.0))
((0 . "LINE") (100 . "AcDbEntity") (8 . "ARCH") (62 . 7) (370 . 13) (100 . "AcDbLine") (10 17171.9457013575
8076.9230769231 0.0) (11 17138.0090497738 8076.9230769231 0.0))
((0 . "LINE") (100 . "AcDbEntity") (8 . "ARCH") (62 . 7) (370 . 13) (100 . "AcDbLine") (10 17138.0090497738
8076.9230769231 0.0) (11 17135.7466063348 8065.6108597285 0.0))
((0 . "LINE") (100 . "AcDbEntity") (8 . "ARCH") (62 . 7) (370 . 13) (100 . "AcDbLine") (10 17135.7466063348
8065.6108597285 0.0) (11 17126.6968325792 8020.3619909502 0.0))
((0 . "LINE") (100 . "AcDbEntity") (8 . "ARCH") (62 . 7) (370 . 13) (100 . "AcDbLine") (10 17126.6968325792
8020.3619909502 0.0) (11 17113.1221719457 7997.7375565611 0.0))
((0 . "LINE") (100 . "AcDbEntity") (8 . "ARCH") (62 . 7) (370 . 13) (100 . "AcDbLine") (10 17113.1221719457
7997.7375565611 0.0) (11 17092.7601809955 7963.8009049774 0.0))
((0 . "LINE") (100 . "AcDbEntity") (8 . "ARCH") (62 . 7) (370 . 13) (100 . "AcDbLine") (10 17092.7601809955
7963.8009049774 0.0) (11 16334.8416289593 7963.8009049774 0.0))
((0 . "LINE") (100 . "AcDbEntity") (8 . "ARCH") (62 . 7) (370 . 13) (100 . "AcDbLine") (10 16334.8416289593
7963.8009049774 0.0) (11 16321.2669683258 7997.7375565611 0.0))
((0 . "LINE") (100 . "AcDbEntity") (8 . "ARCH") (62 . 7) (370 . 13) (100 . "AcDbLine") (10 16321.2669683258
7997.7375565611 0.0) (11 16312.2171945701 8020.3619909502 0.0))
((0 . "LINE") (100 . "AcDbEntity") (8 . "ARCH") (62 . 7) (370 . 13) (100 . "AcDbLine") (10 16312.2171945701
8020.3619909502 0.0) (11 16289.592760181 8065.6108597285 0.0))
((0 . "LINE") (100 . "AcDbEntity") (8 . "ARCH") (62 . 7) (370 . 13) (100 . "AcDbLine") (10 16289.592760181
8065.6108597285 0.0) (11 16278.2805429864 8065.6108597285 0.0))
((0 . "LINE") (100 . "AcDbEntity") (8 . "ARCH") (62 . 7) (370 . 13) (100 . "AcDbLine") (10 16278.2805429864
8065.6108597285 0.0) (11 16278.2805429864 8178.7330316742 0.0))
((0 . "LINE") (100 . "AcDbEntity") (8 . "ARCH") (62 . 7) (370 . 13) (100 . "AcDbLine") (10 16289.592760181
8065.6108597285 0.0) (11 17135.7466063348 8065.6108597285 0.0))
((0 . "LINE") (100 . "AcDbEntity") (8 . "ARCH") (62 . 7) (370 . 13) (100 . "AcDbLine") (10 17135.7466063348
8065.6108597285 0.0) (11 17160.6334841629 8065.6108597285 0.0))
((0 . "LINE") (100 . "AcDbEntity") (8 . "ARCH") (62 . 7) (370 . 13) (100 . "AcDbLine") (10 16321.2669683258
7997.7375565611 0.0) (11 17113.1221719457 7997.7375565611 0.0))
((0 . "LINE") (100 . "AcDbEntity") (8 . "ARCH") (62 . 7) (370 . 13) (100 . "AcDbLine") (10 3710.407239819
7828.0542986425 0.0) (11 7307.6923076923 7828.0542986425 0.0))
((0 . "LINE") (100 . "AcDbEntity") (8 . "ARCH") (62 . 7) (370 . 13) (100 . "AcDbLine") (10 7307.6923076923
7828.0542986425 0.0) (11 7330.3167420814 7828.0542986425 0.0))
((0 . "LINE") (100 . "AcDbEntity") (8 . "ARCH") (62 . 7) (370 . 13) (100 . "AcDbLine") (10 3710.407239819
7760.1809954751 0.0) (11 7330.3167420814 7760.1809954751 0.0))
((0 . "LINE") (100 . "AcDbEntity") (8 . "ARCH") (62 . 7) (370 . 13) (100 . "AcDbLine") (10 3710.407239819
7635.7466063348 0.0) (11 7330.3167420814 7635.7466063348 0.0))
((0 . "LINE") (100 . "AcDbEntity") (8 . "ARCH") (62 . 7) (370 . 13) (100 . "AcDbLine") (10 3710.407239819
7567.8733031674 0.0) (11 4434.3891402715 7567.8733031674 0.0))
((0 . "LINE") (100 . "AcDbEntity") (8 . "ARCH") (62 . 7) (370 . 13) (100 . "AcDbLine") (10 4434.3891402715
7567.8733031674 0.0) (11 4490.9502262443 7567.8733031674 0.0))
((0 . "LINE") (100 . "AcDbEntity") (8 . "ARCH") (62 . 7) (370 . 13) (100 . "AcDbLine") (10 4490.9502262443
7567.8733031674 0.0) (11 7330.3167420814 7567.8733031674 0.0))
((0 . "LINE") (100 . "AcDbEntity") (8 . "ARCH") (62 . 7) (370 . 13) (100 . "AcDbLine") (10 7714.9321266968
7828.0542986425 0.0) (11 7726.2443438914 7828.0542986425 0.0))
((0 . "LINE") (100 . "AcDbEntity") (8 . "ARCH") (62 . 7) (370 . 13) (100 . "AcDbLine") (10 7726.2443438914
7828.0542986425 0.0) (11 8947.963800905 7828.0542986425 0.0))
((0 . "LINE") (100 . "AcDbEntity") (8 . "ARCH") (62 . 7) (370 . 13) (100 . "AcDbLine") (10 7714.9321266968
7760.1809954751 0.0) (11 8947.963800905 7760.1809954751 0.0))
((0 . "LINE") (100 . "AcDbEntity") (8 . "ARCH") (62 . 7) (370 . 13) (100 . "AcDbLine") (10 7714.9321266968
7635.7466063348 0.0) (11 8947.963800905 7635.7466063348 0.0))
((0 . "LINE") (100 . "AcDbEntity") (8 . "ARCH") (62 . 7) (370 . 13) (100 . "AcDbLine") (10 7714.9321266968
7567.8733031674 0.0) (11 8947.963800905 7567.8733031674 0.0))
((0 . "LINE") (100 . "AcDbEntity") (8 . "ARCH") (62 . 7) (370 . 13) (100 . "AcDbLine") (10 9807.6923076923
7828.0542986425 0.0) (11 10316.742081448 7828.0542986425 0.0))
((0 . "LINE") (100 . "AcDbEntity") (8 . "ARCH") (62 . 7) (370 . 13) (100 . "AcDbLine") (10 9807.6923076923
7760.1809954751 0.0) (11 10316.742081448 7760.1809954751 0.0))
((0 . "LINE") (100 . "AcDbEntity") (8 . "ARCH") (62 . 7) (370 . 13) (100 . "AcDbLine") (10 9807.6923076923
7635.7466063348 0.0) (11 10316.742081448 7635.7466063348 0.0))
((0 . "LINE") (100 . "AcDbEntity") (8 . "ARCH") (62 . 7) (370 . 13) (100 . "AcDbLine") (10 9807.6923076923
7567.8733031674 0.0) (11 10316.742081448 7567.8733031674 0.0))
((0 . "LINE") (100 . "AcDbEntity") (8 . "ARCH") (62 . 7) (370 . 13) (100 . "AcDbLine") (10 11085.9728506787
7828.0542986425 0.0) (11 12126.6968325792 7828.0542986425 0.0))
((0 . "LINE") (100 . "AcDbEntity") (8 . "ARCH") (62 . 7) (370 . 13) (100 . "AcDbLine") (10 12126.6968325792
7828.0542986425 0.0) (11 12149.3212669683 7828.0542986425 0.0))
((0 . "LINE") (100 . "AcDbEntity") (8 . "ARCH") (62 . 7) (370 . 13) (100 . "AcDbLine") (10 11085.9728506787
7760.1809954751 0.0) (11 12149.3212669683 7760.1809954751 0.0))
((0 . "LINE") (100 . "AcDbEntity") (8 . "ARCH") (62 . 7) (370 . 13) (100 . "AcDbLine") (10 11085.9728506787
7635.7466063348 0.0) (11 12149.3212669683 7635.7466063348 0.0))
((0 . "LINE") (100 . "AcDbEntity") (8 . "ARCH") (62 . 7) (370 . 13) (100 . "AcDbLine") (10 11085.9728506787
7567.8733031674 0.0) (11 12149.3212669683 7567.8733031674 0.0))
((0 . "LINE") (100 . "AcDbEntity") (8 . "ARCH") (62 . 7) (370 . 13) (100 . "AcDbLine") (10 12590.4977375566
7828.0542986425 0.0) (11 12601.8099547511 7828.0542986425 0.0))
((0 . "LINE") (100 . "AcDbEntity") (8 . "ARCH") (62 . 7) (370 . 13) (100 . "AcDbLine") (10 12601.8099547511
7828.0542986425 0.0) (11 16334.8416289593 7828.0542986425 0.0))
((0 . "LINE") (100 . "AcDbEntity") (8 . "ARCH") (62 . 7) (370 . 13) (100 . "AcDbLine") (10 12590.4977375566
7760.1809954751 0.0) (11 16334.8416289593 7760.1809954751 0.0))
((0 . "LINE") (100 . "AcDbEntity") (8 . "ARCH") (62 . 7) (370 . 13) (100 . "AcDbLine") (10 12590.4977375566
7635.7466063348 0.0) (11 16334.8416289593 7635.7466063348 0.0))
((0 . "LINE") (100 . "AcDbEntity") (8 . "ARCH") (62 . 7) (370 . 13) (100 . "AcDbLine") (10 12590.4977375566
7567.8733031674 0.0) (11 15554.2986425339 7567.8733031674 0.0))
((0 . "LINE") (100 . "AcDbEntity") (8 . "ARCH") (62 . 7) (370 . 13) (100 . "AcDbLine") (10 15554.2986425339
7567.8733031674 0.0) (11 15610.8597285068 7567.8733031674 0.0))
((0 . "LINE") (100 . "AcDbEntity") (8 . "ARCH") (62 . 7) (370 . 13) (100 . "AcDbLine") (10 15610.8597285068
7567.8733031674 0.0) (11 16334.8416289593 7567.8733031674 0.0))
((0 . "LINE") (100 . "AcDbEntity") (8 . "ARCH") (62 . 7) (370 . 13) (100 . "AcDbLine") (10 7307.6923076923
7861.9909502262 0.0) (11 7726.2443438914 7861.9909502262 0.0))
((0 . "LINE") (100 . "AcDbEntity") (8 . "ARCH") (62 . 7) (370 . 13) (100 . "AcDbLine") (10 7726.2443438914
7861.9909502262 0.0) (11 7726.2443438914 7828.0542986425 0.0))
((0 . "LINE") (100 . "AcDbEntity") (8 . "ARCH") (62 . 7) (370 . 13) (100 . "AcDbLine") (10 7726.2443438914
7828.0542986425 0.0) (11 7726.2443438914 7771.4932126697 0.0))
((0 . "LINE") (100 . "AcDbEntity") (8 . "ARCH") (62 . 7) (370 . 13) (100 . "AcDbLine") (10 7726.2443438914
7771.4932126697 0.0) (11 7714.9321266968 7771.4932126697 0.0))
((0 . "LINE") (100 . "AcDbEntity") (8 . "ARCH") (62 . 7) (370 . 13) (100 . "AcDbLine") (10 7714.9321266968
7771.4932126697 0.0) (11 7330.3167420814 7771.4932126697 0.0))
((0 . "LINE") (100 . "AcDbEntity") (8 . "ARCH") (62 . 7) (370 . 13) (100 . "AcDbLine") (10 7330.3167420814
7771.4932126697 0.0) (11 7307.6923076923 7771.4932126697 0.0))
((0 . "LINE") (100 . "AcDbEntity") (8 . "ARCH") (62 . 7) (370 . 13) (100 . "AcDbLine") (10 7307.6923076923
7771.4932126697 0.0) (11 7307.6923076923 7828.0542986425 0.0))
((0 . "LINE") (100 . "AcDbEntity") (8 . "ARCH") (62 . 7) (370 . 13) (100 . "AcDbLine") (10 7307.6923076923
7828.0542986425 0.0) (11 7307.6923076923 7861.9909502262 0.0))
((0 . "LINE") (100 . "AcDbEntity") (8 . "ARCH") (62 . 7) (370 . 13) (100 . "AcDbLine") (10 7714.9321266968
7771.4932126697 0.0) (11 7714.9321266968 7760.1809954751 0.0))
((0 . "LINE") (100 . "AcDbEntity") (8 . "ARCH") (62 . 7) (370 . 13) (100 . "AcDbLine") (10 7714.9321266968
7760.1809954751 0.0) (11 7714.9321266968 7635.7466063348 0.0))
((0 . "LINE") (100 . "AcDbEntity") (8 . "ARCH") (62 . 7) (370 . 13) (100 . "AcDbLine") (10 7714.9321266968
7635.7466063348 0.0) (11 7714.9321266968 7624.4343891403 0.0))
((0 . "LINE") (100 . "AcDbEntity") (8 . "ARCH") (62 . 7) (370 . 13) (100 . "AcDbLine") (10 7714.9321266968
7624.4343891403 0.0) (11 7330.3167420814 7624.4343891403 0.0))
((0 . "LINE") (100 . "AcDbEntity") (8 . "ARCH") (62 . 7) (370 . 13) (100 . "AcDbLine") (10 7330.3167420814
7624.4343891403 0.0) (11 7330.3167420814 7635.7466063348 0.0))
((0 . "LINE") (100 . "AcDbEntity") (8 . "ARCH") (62 . 7) (370 . 13) (100 . "AcDbLine") (10 7330.3167420814
7635.7466063348 0.0) (11 7330.3167420814 7760.1809954751 0.0))
((0 . "LINE") (100 . "AcDbEntity") (8 . "ARCH") (62 . 7) (370 . 13) (100 . "AcDbLine") (10 7330.3167420814
7760.1809954751 0.0) (11 7330.3167420814 7771.4932126697 0.0))
((0 . "LINE") (100 . "AcDbEntity") (8 . "ARCH") (62 . 7) (370 . 13) (100 . "AcDbLine") (10 7330.3167420814
7567.8733031674 0.0) (11 7714.9321266968 7567.8733031674 0.0))
((0 . "LINE") (100 . "AcDbEntity") (8 . "ARCH") (62 . 7) (370 . 13) (100 . "AcDbLine") (10 7330.3167420814
7567.8733031674 0.0) (11 7330.3167420814 7124.8868778281 0.0))
((0 . "LINE") (100 . "AcDbEntity") (8 . "ARCH") (62 . 7) (370 . 13) (100 . "AcDbLine") (10 7714.9321266968
7567.8733031674 0.0) (11 7714.9321266968 7135.398540724 0.0))
((0 . "LINE") (100 . "AcDbEntity") (8 . "ARCH") (62 . 7) (370 . 13) (100 . "AcDbLine") (10 12126.6968325792
7861.9909502262 0.0) (11 12601.8099547511 7861.9909502262 0.0))
((0 . "LINE") (100 . "AcDbEntity") (8 . "ARCH") (62 . 7) (370 . 13) (100 . "AcDbLine") (10 12601.8099547511
7861.9909502262 0.0) (11 12601.8099547511 7828.0542986425 0.0))
((0 . "LINE") (100 . "AcDbEntity") (8 . "ARCH") (62 . 7) (370 . 13) (100 . "AcDbLine") (10 12601.8099547511
7828.0542986425 0.0) (11 12601.8099547511 7771.4932126697 0.0))
((0 . "LINE") (100 . "AcDbEntity") (8 . "ARCH") (62 . 7) (370 . 13) (100 . "AcDbLine") (10 12601.8099547511
7771.4932126697 0.0) (11 12590.4977375566 7771.4932126697 0.0))
((0 . "LINE") (100 . "AcDbEntity") (8 . "ARCH") (62 . 7) (370 . 13) (100 . "AcDbLine") (10 12590.4977375566
7771.4932126697 0.0) (11 12149.3212669683 7771.4932126697 0.0))
((0 . "LINE") (100 . "AcDbEntity") (8 . "ARCH") (62 . 7) (370 . 13) (100 . "AcDbLine") (10 12149.3212669683
7771.4932126697 0.0) (11 12126.6968325792 7771.4932126697 0.0))
((0 . "LINE") (100 . "AcDbEntity") (8 . "ARCH") (62 . 7) (370 . 13) (100 . "AcDbLine") (10 12126.6968325792
7771.4932126697 0.0) (11 12126.6968325792 7828.0542986425 0.0))
((0 . "LINE") (100 . "AcDbEntity") (8 . "ARCH") (62 . 7) (370 . 13) (100 . "AcDbLine") (10 12126.6968325792
7828.0542986425 0.0) (11 12126.6968325792 7861.9909502262 0.0))
((0 . "LINE") (100 . "AcDbEntity") (8 . "ARCH") (62 . 7) (370 . 13) (100 . "AcDbLine") (10 12590.4977375566
7771.4932126697 0.0) (11 12590.4977375566 7760.1809954751 0.0))
((0 . "LINE") (100 . "AcDbEntity") (8 . "ARCH") (62 . 7) (370 . 13) (100 . "AcDbLine") (10 12590.4977375566
7760.1809954751 0.0) (11 12590.4977375566 7635.7466063348 0.0))
((0 . "LINE") (100 . "AcDbEntity") (8 . "ARCH") (62 . 7) (370 . 13) (100 . "AcDbLine") (10 12590.4977375566
7635.7466063348 0.0) (11 12590.4977375566 7624.4343891403 0.0))
((0 . "LINE") (100 . "AcDbEntity") (8 . "ARCH") (62 . 7) (370 . 13) (100 . "AcDbLine") (10 12590.4977375566
7624.4343891403 0.0) (11 12149.3212669683 7624.4343891403 0.0))
((0 . "LINE") (100 . "AcDbEntity") (8 . "ARCH") (62 . 7) (370 . 13) (100 . "AcDbLine") (10 12149.3212669683
7624.4343891403 0.0) (11 12149.3212669683 7635.7466063348 0.0))
((0 . "LINE") (100 . "AcDbEntity") (8 . "ARCH") (62 . 7) (370 . 13) (100 . "AcDbLine") (10 12149.3212669683
7635.7466063348 0.0) (11 12149.3212669683 7760.1809954751 0.0))
((0 . "LINE") (100 . "AcDbEntity") (8 . "ARCH") (62 . 7) (370 . 13) (100 . "AcDbLine") (10 12149.3212669683
7760.1809954751 0.0) (11 12149.3212669683 7771.4932126697 0.0))
((0 . "LINE") (100 . "AcDbEntity") (8 . "ARCH") (62 . 7) (370 . 13) (100 . "AcDbLine") (10 12149.3212669683
7567.8733031674 0.0) (11 12590.4977375566 7567.8733031674 0.0))
((0 . "LINE") (100 . "AcDbEntity") (8 . "ARCH") (62 . 7) (370 . 13) (100 . "AcDbLine") (10 12149.3212669683
7567.8733031674 0.0) (11 12149.3212669683 7130.1396832579 0.0))
((0 . "LINE") (100 . "AcDbEntity") (8 . "ARCH") (62 . 7) (370 . 13) (100 . "AcDbLine") (10 12590.4977375566
7567.8733031674 0.0) (11 12590.4977375566 7081.4479638009 0.0))
((0 . "LINE") (100 . "AcDbEntity") (8 . "ARCH") (62 . 7) (370 . 13) (100 . "AcDbLine") (10 4434.3891402715
7567.8733031674 0.0) (11 4434.3891402715 6900.4524886878 0.0))
((0 . "LINE") (100 . "AcDbEntity") (8 . "ARCH") (62 . 7) (370 . 13) (100 . "AcDbLine") (10 4434.3891402715
6730.7692307692 0.0) (11 4434.3891402715 6549.7737556561 0.0))
((0 . "LINE") (100 . "AcDbEntity") (8 . "ARCH") (62 . 7) (370 . 13) (100 . "AcDbLine") (10 4490.9502262443
7567.8733031674 0.0) (11 4490.9502262443 6549.7737556561 0.0))
((0 . "LINE") (100 . "AcDbEntity") (8 . "ARCH") (62 . 7) (370 . 13) (100 . "AcDbLine") (10 15554.2986425339
7567.8733031674 0.0) (11 15554.2986425339 6549.7737556561 0.0))
((0 . "LINE") (100 . "AcDbEntity") (8 . "ARCH") (62 . 7) (370 . 13) (100 . "AcDbLine") (10 15610.8597285068
7567.8733031674 0.0) (11 15610.8597285068 6887.25489819 0.0))
((0 . "LINE") (100 . "AcDbEntity") (8 . "ARCH") (62 . 7) (370 . 13) (100 . "AcDbLine") (10 15610.8597285068
6730.7692307692 0.0) (11 15610.8597285068 6549.7737556561 0.0))
((0 . "LINE") (100 . "AcDbEntity") (8 . "ARCH") (62 . 7) (370 . 13) (100 . "AcDbLine") (10 8947.963800905
7647.0588235294 0.0) (11 9807.6923076923 7647.0588235294 0.0))
((0 . "LINE") (100 . "AcDbEntity") (8 . "ARCH") (62 . 7) (370 . 13) (100 . "AcDbLine") (10 9807.6923076923
7647.0588235294 0.0) (11 9807.6923076923 7635.7466063348 0.0))
((0 . "LINE") (100 . "AcDbEntity") (8 . "ARCH") (62 . 7) (370 . 13) (100 . "AcDbLine") (10 9807.6923076923
7635.7466063348 0.0) (11 9807.6923076923 7567.8733031674 0.0))
((0 . "LINE") (100 . "AcDbEntity") (8 . "ARCH") (62 . 7) (370 . 13) (100 . "AcDbLine") (10 9807.6923076923
7567.8733031674 0.0) (11 9807.6923076923 6809.9547511312 0.0))
((0 . "LINE") (100 . "AcDbEntity") (8 . "ARCH") (62 . 7) (370 . 13) (100 . "AcDbLine") (10 8947.963800905
6549.7737556561 0.0) (11 8947.963800905 7567.8733031674 0.0))
((0 . "LINE") (100 . "AcDbEntity") (8 . "ARCH") (62 . 7) (370 . 13) (100 . "AcDbLine") (10 8947.963800905
7567.8733031674 0.0) (11 8947.963800905 7635.7466063348 0.0))
((0 . "LINE") (100 . "AcDbEntity") (8 . "ARCH") (62 . 7) (370 . 13) (100 . "AcDbLine") (10 8947.963800905
7635.7466063348 0.0) (11 8947.963800905 7647.0588235294 0.0))
((0 . "LINE") (100 . "AcDbEntity") (8 . "ARCH") (62 . 7) (370 . 13) (100 . "AcDbLine") (10 9004.5248868778
7601.8099547511 0.0) (11 9751.1312217195 7601.8099547511 0.0))
((0 . "LINE") (100 . "AcDbEntity") (8 . "ARCH") (62 . 7) (370 . 13) (100 . "AcDbLine") (10 9751.1312217195
7601.8099547511 0.0) (11 9751.1312217195 6809.9547511312 0.0))
((0 . "LINE") (100 . "AcDbEntity") (8 . "ARCH") (62 . 7) (370 . 13) (100 . "AcDbLine") (10 9004.5248868778
6549.7737556561 0.0) (11 9004.5248868778 7601.8099547511 0.0))
((0 . "LINE") (100 . "AcDbEntity") (8 . "ARCH") (62 . 7) (370 . 13) (100 . "AcDbLine") (10 9106.334841629 7500 0.0) (11
9649.3212669683 7500 0.0))
((0 . "LINE") (100 . "AcDbEntity") (8 . "ARCH") (62 . 7) (370 . 13) (100 . "AcDbLine") (10 9649.3212669683 7500 0.0) (11
9649.3212669683 6866.5158371041 0.0))
((0 . "LINE") (100 . "AcDbEntity") (8 . "ARCH") (62 . 7) (370 . 13) (100 . "AcDbLine") (10 9649.3212669683
6866.5158371041 0.0) (11 9106.334841629 6866.5158371041 0.0))
((0 . "LINE") (100 . "AcDbEntity") (8 . "ARCH") (62 . 7) (370 . 13) (100 . "AcDbLine") (10 9106.334841629
6866.5158371041 0.0) (11 9106.334841629 7500 0.0))
((0 . "LINE") (100 . "AcDbEntity") (8 . "ARCH") (62 . 7) (370 . 13) (100 . "AcDbLine") (10 9151.5837104072
7454.7511312217 0.0) (11 9604.07239819 7454.7511312217 0.0))
((0 . "LINE") (100 . "AcDbEntity") (8 . "ARCH") (62 . 7) (370 . 13) (100 . "AcDbLine") (10 9604.07239819 7454.7511312217
0.0) (11 9604.07239819 6900.4524886878 0.0))
((0 . "LINE") (100 . "AcDbEntity") (8 . "ARCH") (62 . 7) (370 . 13) (100 . "AcDbLine") (10 9604.07239819 6900.4524886878
0.0) (11 9151.5837104072 6900.4524886878 0.0))
((0 . "LINE") (100 . "AcDbEntity") (8 . "ARCH") (62 . 7) (370 . 13) (100 . "AcDbLine") (10 9151.5837104072
6900.4524886878 0.0) (11 9151.5837104072 7454.7511312217 0.0))
((0 . "LINE") (100 . "AcDbEntity") (8 . "ARCH") (62 . 7) (370 . 13) (100 . "AcDbLine") (10 9185.520361991 7420.814479638
0.0) (11 9570.1357466063 7420.814479638 0.0))
((0 . "LINE") (100 . "AcDbEntity") (8 . "ARCH") (62 . 7) (370 . 13) (100 . "AcDbLine") (10 9570.1357466063
7420.814479638 0.0) (11 9570.1357466063 6934.3891402715 0.0))
((0 . "LINE") (100 . "AcDbEntity") (8 . "ARCH") (62 . 7) (370 . 13) (100 . "AcDbLine") (10 9570.1357466063
6934.3891402715 0.0) (11 9185.520361991 6934.3891402715 0.0))
((0 . "LINE") (100 . "AcDbEntity") (8 . "ARCH") (62 . 7) (370 . 13) (100 . "AcDbLine") (10 9185.520361991
6934.3891402715 0.0) (11 9185.520361991 7420.814479638 0.0))
((0 . "LINE") (100 . "AcDbEntity") (8 . "ARCH") (62 . 7) (370 . 13) (100 . "AcDbLine") (10 9106.334841629
6855.2036199095 0.0) (11 9649.3212669683 6855.2036199095 0.0))
((0 . "LINE") (100 . "AcDbEntity") (8 . "ARCH") (62 . 7) (370 . 13) (100 . "AcDbLine") (10 9649.3212669683
6855.2036199095 0.0) (11 9649.3212669683 6809.9547511312 0.0))
((0 . "LINE") (100 . "AcDbEntity") (8 . "ARCH") (62 . 7) (370 . 13) (100 . "AcDbLine") (10 9106.334841629
6549.7737556561 0.0) (11 9106.334841629 6607.2624434389 0.0))
((0 . "LINE") (100 . "AcDbEntity") (8 . "ARCH") (62 . 7) (370 . 13) (100 . "AcDbLine") (10 9106.334841629
6607.2624434389 0.0) (11 9106.334841629 6643.0995475113 0.0))
((0 . "LINE") (100 . "AcDbEntity") (8 . "ARCH") (62 . 7) (370 . 13) (100 . "AcDbLine") (10 9106.334841629
6643.0995475113 0.0) (11 9106.334841629 6710.6787330317 0.0))
((0 . "LINE") (100 . "AcDbEntity") (8 . "ARCH") (62 . 7) (370 . 13) (100 . "AcDbLine") (10 9106.334841629
6710.6787330317 0.0) (11 9106.334841629 6762.4547511312 0.0))
((0 . "LINE") (100 . "AcDbEntity") (8 . "ARCH") (62 . 7) (370 . 13) (100 . "AcDbLine") (10 9106.334841629
6762.4547511312 0.0) (11 9106.334841629 6855.2036199095 0.0))
((0 . "LINE") (100 . "AcDbEntity") (8 . "ARCH") (62 . 7) (370 . 13) (100 . "AcDbLine") (10 10316.742081448
7647.0588235294 0.0) (11 11085.9728506787 7647.0588235294 0.0))
((0 . "LINE") (100 . "AcDbEntity") (8 . "ARCH") (62 . 7) (370 . 13) (100 . "AcDbLine") (10 11085.9728506787
7647.0588235294 0.0) (11 11085.9728506787 7635.7466063348 0.0))
((0 . "LINE") (100 . "AcDbEntity") (8 . "ARCH") (62 . 7) (370 . 13) (100 . "AcDbLine") (10 11085.9728506787
7635.7466063348 0.0) (11 11085.9728506787 7567.8733031674 0.0))
((0 . "LINE") (100 . "AcDbEntity") (8 . "ARCH") (62 . 7) (370 . 13) (100 . "AcDbLine") (10 11085.9728506787
7567.8733031674 0.0) (11 11085.9728506787 6549.7737556561 0.0))
((0 . "LINE") (100 . "AcDbEntity") (8 . "ARCH") (62 . 7) (370 . 13) (100 . "AcDbLine") (10 10316.742081448
6809.9547511312 0.0) (11 10316.742081448 7567.8733031674 0.0))
((0 . "LINE") (100 . "AcDbEntity") (8 . "ARCH") (62 . 7) (370 . 13) (100 . "AcDbLine") (10 10316.742081448
7567.8733031674 0.0) (11 10316.742081448 7635.7466063348 0.0))
((0 . "LINE") (100 . "AcDbEntity") (8 . "ARCH") (62 . 7) (370 . 13) (100 . "AcDbLine") (10 10316.742081448
7635.7466063348 0.0) (11 10316.742081448 7647.0588235294 0.0))
((0 . "LINE") (100 . "AcDbEntity") (8 . "ARCH") (62 . 7) (370 . 13) (100 . "AcDbLine") (10 10373.3031674208
7601.8099547511 0.0) (11 11029.4117647059 7601.8099547511 0.0))
((0 . "LINE") (100 . "AcDbEntity") (8 . "ARCH") (62 . 7) (370 . 13) (100 . "AcDbLine") (10 11029.4117647059
7601.8099547511 0.0) (11 11029.4117647059 6549.7737556561 0.0))
((0 . "LINE") (100 . "AcDbEntity") (8 . "ARCH") (62 . 7) (370 . 13) (100 . "AcDbLine") (10 10373.3031674208
6809.9547511312 0.0) (11 10373.3031674208 7601.8099547511 0.0))
((0 . "LINE") (100 . "AcDbEntity") (8 . "ARCH") (62 . 7) (370 . 13) (100 . "AcDbLine") (10 10475.1131221719 7500 0.0)
(11 10927.6018099548 7500 0.0))
((0 . "LINE") (100 . "AcDbEntity") (8 . "ARCH") (62 . 7) (370 . 13) (100 . "AcDbLine") (10 10927.6018099548 7500 0.0)
(11 10927.6018099548 6866.5158371041 0.0))
((0 . "LINE") (100 . "AcDbEntity") (8 . "ARCH") (62 . 7) (370 . 13) (100 . "AcDbLine") (10 10927.6018099548
6866.5158371041 0.0) (11 10475.1131221719 6866.5158371041 0.0))
((0 . "LINE") (100 . "AcDbEntity") (8 . "ARCH") (62 . 7) (370 . 13) (100 . "AcDbLine") (10 10475.1131221719
6866.5158371041 0.0) (11 10475.1131221719 7500 0.0))
((0 . "LINE") (100 . "AcDbEntity") (8 . "ARCH") (62 . 7) (370 . 13) (100 . "AcDbLine") (10 10520.3619909502
7454.7511312217 0.0) (11 10882.3529411765 7454.7511312217 0.0))
((0 . "LINE") (100 . "AcDbEntity") (8 . "ARCH") (62 . 7) (370 . 13) (100 . "AcDbLine") (10 10882.3529411765
7454.7511312217 0.0) (11 10882.3529411765 6900.4524886878 0.0))
((0 . "LINE") (100 . "AcDbEntity") (8 . "ARCH") (62 . 7) (370 . 13) (100 . "AcDbLine") (10 10882.3529411765
6900.4524886878 0.0) (11 10520.3619909502 6900.4524886878 0.0))
((0 . "LINE") (100 . "AcDbEntity") (8 . "ARCH") (62 . 7) (370 . 13) (100 . "AcDbLine") (10 10520.3619909502
6900.4524886878 0.0) (11 10520.3619909502 7454.7511312217 0.0))
((0 . "LINE") (100 . "AcDbEntity") (8 . "ARCH") (62 . 7) (370 . 13) (100 . "AcDbLine") (10 10554.2986425339
7420.814479638 0.0) (11 10848.4162895928 7420.814479638 0.0))
((0 . "LINE") (100 . "AcDbEntity") (8 . "ARCH") (62 . 7) (370 . 13) (100 . "AcDbLine") (10 10848.4162895928
7420.814479638 0.0) (11 10848.4162895928 6934.3891402715 0.0))
((0 . "LINE") (100 . "AcDbEntity") (8 . "ARCH") (62 . 7) (370 . 13) (100 . "AcDbLine") (10 10848.4162895928
6934.3891402715 0.0) (11 10554.2986425339 6934.3891402715 0.0))
((0 . "LINE") (100 . "AcDbEntity") (8 . "ARCH") (62 . 7) (370 . 13) (100 . "AcDbLine") (10 10554.2986425339
6934.3891402715 0.0) (11 10554.2986425339 7420.814479638 0.0))
((0 . "LINE") (100 . "AcDbEntity") (8 . "ARCH") (62 . 7) (370 . 13) (100 . "AcDbLine") (10 10475.1131221719
6855.2036199095 0.0) (11 10927.6018099548 6855.2036199095 0.0))
((0 . "LINE") (100 . "AcDbEntity") (8 . "ARCH") (62 . 7) (370 . 13) (100 . "AcDbLine") (10 10927.6018099548
6855.2036199095 0.0) (11 10927.6018099548 6761.8212669683 0.0))
((0 . "LINE") (100 . "AcDbEntity") (8 . "ARCH") (62 . 7) (370 . 13) (100 . "AcDbLine") (10 10927.6018099548
6761.8212669683 0.0) (11 10927.6018099548 6717.7488687783 0.0))
((0 . "LINE") (100 . "AcDbEntity") (8 . "ARCH") (62 . 7) (370 . 13) (100 . "AcDbLine") (10 10927.6018099548
6717.7488687783 0.0) (11 10927.6018099548 6687.9524886878 0.0))
((0 . "LINE") (100 . "AcDbEntity") (8 . "ARCH") (62 . 7) (370 . 13) (100 . "AcDbLine") (10 10927.6018099548
6687.9524886878 0.0) (11 10927.6018099548 6641.3122171946 0.0))
((0 . "LINE") (100 . "AcDbEntity") (8 . "ARCH") (62 . 7) (370 . 13) (100 . "AcDbLine") (10 10927.6018099548
6641.3122171946 0.0) (11 10927.6018099548 6607.0701357466 0.0))
((0 . "LINE") (100 . "AcDbEntity") (8 . "ARCH") (62 . 7) (370 . 13) (100 . "AcDbLine") (10 10927.6018099548
6607.0701357466 0.0) (11 10927.6018099548 6549.7737556561 0.0))
((0 . "LINE") (100 . "AcDbEntity") (8 . "ARCH") (62 . 7) (370 . 13) (100 . "AcDbLine") (10 10475.1131221719
6809.9547511312 0.0) (11 10475.1131221719 6855.2036199095 0.0))
((0 . "LINE") (100 . "AcDbEntity") (8 . "ARCH") (62 . 7) (370 . 13) (100 . "AcDbLine") (10 4004.5248868778
5916.2895927602 0.0) (11 4208.1447963801 6052.036199095 0.0))
((0 . "LINE") (100 . "AcDbEntity") (8 . "ARCH") (62 . 7) (370 . 13) (100 . "AcDbLine") (10 4208.1447963801
6052.036199095 0.0) (11 6606.334841629 6052.036199095 0.0))
((0 . "LINE") (100 . "AcDbEntity") (8 . "ARCH") (62 . 7) (370 . 13) (100 . "AcDbLine") (10 6606.334841629 6052.036199095
0.0) (11 6843.8914027149 5916.2895927602 0.0))
((0 . "LINE") (100 . "AcDbEntity") (8 . "ARCH") (62 . 7) (370 . 13) (100 . "AcDbLine") (10 4004.5248868778
5916.2895927602 0.0) (11 6843.8914027149 5916.2895927602 0.0))
((0 . "LINE") (100 . "AcDbEntity") (8 . "ARCH") (62 . 7) (370 . 13) (100 . "AcDbLine") (10 6843.8914027149
5916.2895927602 0.0) (11 6843.8914027149 5848.4162895928 0.0))
((0 . "LINE") (100 . "AcDbEntity") (8 . "ARCH") (62 . 7) (370 . 13) (100 . "AcDbLine") (10 6843.8914027149
5848.4162895928 0.0) (11 4004.5248868778 5848.4162895928 0.0))
((0 . "LINE") (100 . "AcDbEntity") (8 . "ARCH") (62 . 7) (370 . 13) (100 . "AcDbLine") (10 4004.5248868778
5848.4162895928 0.0) (11 4004.5248868778 5916.2895927602 0.0))
((0 . "LINE") (100 . "AcDbEntity") (8 . "ARCH") (62 . 7) (370 . 13) (100 . "AcDbLine") (10 4004.5248868778
5848.4162895928 0.0) (11 4004.5248868778 5814.4796380091 0.0))
((0 . "LINE") (100 . "AcDbEntity") (8 . "ARCH") (62 . 7) (370 . 13) (100 . "AcDbLine") (10 4004.5248868778
5814.4796380091 0.0) (11 4004.5248868778 5791.8552036199 0.0))
((0 . "LINE") (100 . "AcDbEntity") (8 . "ARCH") (62 . 7) (370 . 13) (100 . "AcDbLine") (10 4004.5248868778
5791.8552036199 0.0) (11 4083.7104072398 5757.9185520362 0.0))
((0 . "LINE") (100 . "AcDbEntity") (8 . "ARCH") (62 . 7) (370 . 13) (100 . "AcDbLine") (10 4083.7104072398
5757.9185520362 0.0) (11 6753.3936651584 5757.9185520362 0.0))
((0 . "LINE") (100 . "AcDbEntity") (8 . "ARCH") (62 . 7) (370 . 13) (100 . "AcDbLine") (10 6753.3936651584
5757.9185520362 0.0) (11 6843.8914027149 5791.8552036199 0.0))
((0 . "LINE") (100 . "AcDbEntity") (8 . "ARCH") (62 . 7) (370 . 13) (100 . "AcDbLine") (10 6843.8914027149
5791.8552036199 0.0) (11 6843.8914027149 5814.4796380091 0.0))
((0 . "LINE") (100 . "AcDbEntity") (8 . "ARCH") (62 . 7) (370 . 13) (100 . "AcDbLine") (10 6843.8914027149
5814.4796380091 0.0) (11 6843.8914027149 5848.4162895928 0.0))
((0 . "LINE") (100 . "AcDbEntity") (8 . "ARCH") (62 . 7) (370 . 13) (100 . "AcDbLine") (10 4038.4615384615
5757.9185520362 0.0) (11 4083.7104072398 5757.9185520362 0.0))
((0 . "LINE") (100 . "AcDbEntity") (8 . "ARCH") (62 . 7) (370 . 13) (100 . "AcDbLine") (10 6753.3936651584
5757.9185520362 0.0) (11 6787.3303167421 5757.9185520362 0.0))
((0 . "LINE") (100 . "AcDbEntity") (8 . "ARCH") (62 . 7) (370 . 13) (100 . "AcDbLine") (10 6787.3303167421
5757.9185520362 0.0) (11 6787.3303167421 5746.6063348416 0.0))
((0 . "LINE") (100 . "AcDbEntity") (8 . "ARCH") (62 . 7) (370 . 13) (100 . "AcDbLine") (10 6787.3303167421
5746.6063348416 0.0) (11 6787.3303167421 5701.3574660633 0.0))
((0 . "LINE") (100 . "AcDbEntity") (8 . "ARCH") (62 . 7) (370 . 13) (100 . "AcDbLine") (10 6787.3303167421
5701.3574660633 0.0) (11 6708.1447963801 5701.3574660633 0.0))
((0 . "LINE") (100 . "AcDbEntity") (8 . "ARCH") (62 . 7) (370 . 13) (100 . "AcDbLine") (10 6708.1447963801
5701.3574660633 0.0) (11 4140.2714932127 5701.3574660633 0.0))
((0 . "LINE") (100 . "AcDbEntity") (8 . "ARCH") (62 . 7) (370 . 13) (100 . "AcDbLine") (10 4140.2714932127
5701.3574660633 0.0) (11 4038.4615384615 5701.3574660633 0.0))
((0 . "LINE") (100 . "AcDbEntity") (8 . "ARCH") (62 . 7) (370 . 13) (100 . "AcDbLine") (10 4038.4615384615
5701.3574660633 0.0) (11 4038.4615384615 5746.6063348416 0.0))
((0 . "LINE") (100 . "AcDbEntity") (8 . "ARCH") (62 . 7) (370 . 13) (100 . "AcDbLine") (10 4038.4615384615
5746.6063348416 0.0) (11 4038.4615384615 5757.9185520362 0.0))
((0 . "LINE") (100 . "AcDbEntity") (8 . "ARCH") (62 . 7) (370 . 13) (100 . "AcDbLine") (10 6708.1447963801
5701.3574660633 0.0) (11 6708.1447963801 5656.1085972851 0.0))
((0 . "LINE") (100 . "AcDbEntity") (8 . "ARCH") (62 . 7) (370 . 13) (100 . "AcDbLine") (10 6708.1447963801
5656.1085972851 0.0) (11 6674.2081447964 5622.1719457014 0.0))
((0 . "LINE") (100 . "AcDbEntity") (8 . "ARCH") (62 . 7) (370 . 13) (100 . "AcDbLine") (10 6674.2081447964
5622.1719457014 0.0) (11 6674.2081447964 5588.2352941176 0.0))
((0 . "LINE") (100 . "AcDbEntity") (8 . "ARCH") (62 . 7) (370 . 13) (100 . "AcDbLine") (10 6674.2081447964
5588.2352941176 0.0) (11 6674.2081447964 5576.9230769231 0.0))
((0 . "LINE") (100 . "AcDbEntity") (8 . "ARCH") (62 . 7) (370 . 13) (100 . "AcDbLine") (10 6674.2081447964
5576.9230769231 0.0) (11 4162.8959276018 5576.9230769231 0.0))
((0 . "LINE") (100 . "AcDbEntity") (8 . "ARCH") (62 . 7) (370 . 13) (100 . "AcDbLine") (10 4162.8959276018
5576.9230769231 0.0) (11 4162.8959276018 5588.2352941176 0.0))
((0 . "LINE") (100 . "AcDbEntity") (8 . "ARCH") (62 . 7) (370 . 13) (100 . "AcDbLine") (10 4162.8959276018
5588.2352941176 0.0) (11 4162.8959276018 5610.8597285068 0.0))
((0 . "LINE") (100 . "AcDbEntity") (8 . "ARCH") (62 . 7) (370 . 13) (100 . "AcDbLine") (10 4162.8959276018
5610.8597285068 0.0) (11 4162.8959276018 5622.1719457014 0.0))
((0 . "LINE") (100 . "AcDbEntity") (8 . "ARCH") (62 . 7) (370 . 13) (100 . "AcDbLine") (10 4162.8959276018
5622.1719457014 0.0) (11 4140.2714932127 5656.1085972851 0.0))
((0 . "LINE") (100 . "AcDbEntity") (8 . "ARCH") (62 . 7) (370 . 13) (100 . "AcDbLine") (10 4140.2714932127
5656.1085972851 0.0) (11 4140.2714932127 5701.3574660633 0.0))
((0 . "LINE") (100 . "AcDbEntity") (8 . "ARCH") (62 . 7) (370 . 13) (100 . "AcDbLine") (10 4174.2081447964
5531.6742081448 0.0) (11 4233.0656108597 5531.6742081448 0.0))
((0 . "LINE") (100 . "AcDbEntity") (8 . "ARCH") (62 . 7) (370 . 13) (100 . "AcDbLine") (10 4233.0656108597
5531.6742081448 0.0) (11 4252.1719457014 5531.6742081448 0.0))
((0 . "LINE") (100 . "AcDbEntity") (8 . "LOUVERS") (62 . 7) (370 . 13) (100 . "AcDbLine") (10 4252.1719457014
5531.6742081448 0.0) (11 4310.9502262443 5531.6742081448 0.0))
((0 . "LINE") (100 . "AcDbEntity") (8 . "LOUVERS") (62 . 7) (370 . 13) (100 . "AcDbLine") (10 4310.9502262443
5531.6742081448 0.0) (11 4331.0859728507 5531.6742081448 0.0))
((0 . "LINE") (100 . "AcDbEntity") (8 . "LOUVERS") (62 . 7) (370 . 13) (100 . "AcDbLine") (10 4331.0859728507
5531.6742081448 0.0) (11 4392.8959276018 5531.6742081448 0.0))
((0 . "LINE") (100 . "AcDbEntity") (8 . "LOUVERS") (62 . 7) (370 . 13) (100 . "AcDbLine") (10 4392.8959276018
5531.6742081448 0.0) (11 4460.6221719457 5531.6742081448 0.0))
((0 . "LINE") (100 . "AcDbEntity") (8 . "LOUVERS") (62 . 7) (370 . 13) (100 . "AcDbLine") (10 4460.6221719457
5531.6742081448 0.0) (11 4499.0384615385 5531.6742081448 0.0))
((0 . "LINE") (100 . "AcDbEntity") (8 . "LOUVERS") (62 . 7) (370 . 13) (100 . "AcDbLine") (10 4499.0384615385
5531.6742081448 0.0) (11 4578.9592760181 5531.6742081448 0.0))
((0 . "LINE") (100 . "AcDbEntity") (8 . "LOUVERS") (62 . 7) (370 . 13) (100 . "AcDbLine") (10 4578.9592760181
5531.6742081448 0.0) (11 4640.7918552036 5531.6742081448 0.0))
((0 . "LINE") (100 . "AcDbEntity") (8 . "LOUVERS") (62 . 7) (370 . 13) (100 . "AcDbLine") (10 4640.7918552036
5531.6742081448 0.0) (11 4671.9457013575 5531.6742081448 0.0))
((0 . "LINE") (100 . "AcDbEntity") (8 . "ARCH") (62 . 7) (370 . 13) (100 . "AcDbLine") (10 4671.9457013575
5531.6742081448 0.0) (11 6210.407239819 5531.6742081448 0.0))
((0 . "LINE") (100 . "AcDbEntity") (8 . "LOUVERS") (62 . 7) (370 . 13) (100 . "AcDbLine") (10 6210.407239819
5531.6742081448 0.0) (11 6234.2647058824 5531.6742081448 0.0))
((0 . "LINE") (100 . "AcDbEntity") (8 . "LOUVERS") (62 . 7) (370 . 13) (100 . "AcDbLine") (10 6234.2647058824
5531.6742081448 0.0) (11 6294.2194570136 5531.6742081448 0.0))
((0 . "LINE") (100 . "AcDbEntity") (8 . "LOUVERS") (62 . 7) (370 . 13) (100 . "AcDbLine") (10 6294.2194570136
5531.6742081448 0.0) (11 6374.4230769231 5531.6742081448 0.0))
((0 . "LINE") (100 . "AcDbEntity") (8 . "LOUVERS") (62 . 7) (370 . 13) (100 . "AcDbLine") (10 6374.4230769231
5531.6742081448 0.0) (11 6454.7737556561 5531.6742081448 0.0))
((0 . "LINE") (100 . "AcDbEntity") (8 . "LOUVERS") (62 . 7) (370 . 13) (100 . "AcDbLine") (10 6454.7737556561
5531.6742081448 0.0) (11 6508.2918552036 5531.6742081448 0.0))
((0 . "LINE") (100 . "AcDbEntity") (8 . "LOUVERS") (62 . 7) (370 . 13) (100 . "AcDbLine") (10 6508.2918552036
5531.6742081448 0.0) (11 6523.9932126697 5531.6742081448 0.0))
((0 . "LINE") (100 . "AcDbEntity") (8 . "LOUVERS") (62 . 7) (370 . 13) (100 . "AcDbLine") (10 6523.9932126697
5531.6742081448 0.0) (11 6582.5113122172 5531.6742081448 0.0))
((0 . "LINE") (100 . "AcDbEntity") (8 . "LOUVERS") (62 . 7) (370 . 13) (100 . "AcDbLine") (10 6582.5113122172
5531.6742081448 0.0) (11 6658.6312217195 5531.6742081448 0.0))
((0 . "LINE") (100 . "AcDbEntity") (8 . "LOUVERS") (62 . 7) (370 . 13) (100 . "AcDbLine") (10 6658.6312217195
5531.6742081448 0.0) (11 6674.2081447964 5531.6742081448 0.0))
((0 . "LINE") (100 . "AcDbEntity") (8 . "ARCH") (62 . 7) (370 . 13) (100 . "AcDbLine") (10 4162.8959276018
5588.2352941176 0.0) (11 6674.2081447964 5588.2352941176 0.0))
((0 . "LINE") (100 . "AcDbEntity") (8 . "ARCH") (62 . 7) (370 . 13) (100 . "AcDbLine") (10 6674.2081447964
5588.2352941176 0.0) (11 6685.520361991 5588.2352941176 0.0))
((0 . "LINE") (100 . "AcDbEntity") (8 . "ARCH") (62 . 7) (370 . 13) (100 . "AcDbLine") (10 6787.3303167421
3733.0316742081 0.0) (11 6787.3303167421 3721.7194570136 0.0))
((0 . "LINE") (100 . "AcDbEntity") (8 . "ARCH") (62 . 7) (370 . 13) (100 . "AcDbLine") (10 6787.3303167421
3721.7194570136 0.0) (11 6787.3303167421 3585.9728506787 0.0))
((0 . "LINE") (100 . "AcDbEntity") (8 . "ARCH") (62 . 7) (370 . 13) (100 . "AcDbLine") (10 6787.3303167421
3585.9728506787 0.0) (11 6787.3303167421 3235.2941176471 0.0))
((0 . "LINE") (100 . "AcDbEntity") (8 . "ARCH") (62 . 7) (370 . 13) (100 . "AcDbLine") (10 6787.3303167421
3235.2941176471 0.0) (11 6776.0180995475 3235.2941176471 0.0))
((0 . "LINE") (100 . "AcDbEntity") (8 . "ARCH") (62 . 7) (370 . 13) (100 . "AcDbLine") (10 6776.0180995475
3235.2941176471 0.0) (11 4462.6696832579 3235.2941176471 0.0))
((0 . "LINE") (100 . "AcDbEntity") (8 . "ARCH") (62 . 7) (370 . 13) (100 . "AcDbLine") (10 4360.8597285068
3235.2941176471 0.0) (11 4049.7737556561 3235.2941176471 0.0))
((0 . "LINE") (100 . "AcDbEntity") (8 . "ARCH") (62 . 7) (370 . 13) (100 . "AcDbLine") (10 4049.7737556561
3235.2941176471 0.0) (11 4038.4615384615 3235.2941176471 0.0))
((0 . "LINE") (100 . "AcDbEntity") (8 . "ARCH") (62 . 7) (370 . 13) (100 . "AcDbLine") (10 4038.4615384615
3235.2941176471 0.0) (11 4038.4615384615 3585.9728506787 0.0))
((0 . "LINE") (100 . "AcDbEntity") (8 . "ARCH") (62 . 7) (370 . 13) (100 . "AcDbLine") (10 4038.4615384615
3585.9728506787 0.0) (11 4038.4615384615 3721.7194570136 0.0))
((0 . "LINE") (100 . "AcDbEntity") (8 . "ARCH") (62 . 7) (370 . 13) (100 . "AcDbLine") (10 4038.4615384615
3721.7194570136 0.0) (11 4038.4615384615 3733.0316742081 0.0))
((0 . "LINE") (100 . "AcDbEntity") (8 . "ARCH") (62 . 7) (370 . 13) (100 . "AcDbLine") (10 6776.0180995475
3235.2941176471 0.0) (11 6776.0180995475 2941.1764705882 0.0))
((0 . "LINE") (100 . "AcDbEntity") (8 . "ARCH") (62 . 7) (370 . 13) (100 . "AcDbLine") (10 6776.0180995475
2941.1764705882 0.0) (11 4049.7737556561 2941.1764705882 0.0))
((0 . "LINE") (100 . "AcDbEntity") (8 . "ARCH") (62 . 7) (370 . 13) (100 . "AcDbLine") (10 4049.7737556561
2941.1764705882 0.0) (11 4049.7737556561 3235.2941176471 0.0))
((0 . "LINE") (100 . "AcDbEntity") (8 . "ARCH") (62 . 7) (370 . 13) (100 . "AcDbLine") (10 4027.149321267
2941.1764705882 0.0) (11 4049.7737556561 2941.1764705882 0.0))
((0 . "LINE") (100 . "AcDbEntity") (8 . "ARCH") (62 . 7) (370 . 13) (100 . "AcDbLine") (10 6776.0180995475
2941.1764705882 0.0) (11 6787.3303167421 2941.1764705882 0.0))
((0 . "LINE") (100 . "AcDbEntity") (8 . "ARCH") (62 . 7) (370 . 13) (100 . "AcDbLine") (10 6787.3303167421
2941.1764705882 0.0) (11 6787.3303167421 2861.9909502262 0.0))
((0 . "LINE") (100 . "AcDbEntity") (8 . "ARCH") (62 . 7) (370 . 13) (100 . "AcDbLine") (10 6787.3303167421
2861.9909502262 0.0) (11 6764.7058823529 2861.9909502262 0.0))
((0 . "LINE") (100 . "AcDbEntity") (8 . "ARCH") (62 . 7) (370 . 13) (100 . "AcDbLine") (10 6764.7058823529
2861.9909502262 0.0) (11 4049.7737556561 2861.9909502262 0.0))
((0 . "LINE") (100 . "AcDbEntity") (8 . "ARCH") (62 . 7) (370 . 13) (100 . "AcDbLine") (10 4049.7737556561
2861.9909502262 0.0) (11 4027.149321267 2861.9909502262 0.0))
((0 . "LINE") (100 . "AcDbEntity") (8 . "ARCH") (62 . 7) (370 . 13) (100 . "AcDbLine") (10 4027.149321267
2861.9909502262 0.0) (11 4027.149321267 2941.1764705882 0.0))
((0 . "LINE") (100 . "AcDbEntity") (8 . "ARCH") (62 . 7) (370 . 13) (100 . "AcDbLine") (10 4049.7737556561
2861.9909502262 0.0) (11 4117.6470588235 2794.1176470588 0.0))
((0 . "LINE") (100 . "AcDbEntity") (8 . "ARCH") (62 . 7) (370 . 13) (100 . "AcDbLine") (10 4117.6470588235
2794.1176470588 0.0) (11 4128.9592760181 2748.8687782805 0.0))
((0 . "LINE") (100 . "AcDbEntity") (8 . "ARCH") (62 . 7) (370 . 13) (100 . "AcDbLine") (10 4128.9592760181
2748.8687782805 0.0) (11 4140.2714932127 2703.6199095023 0.0))
((0 . "LINE") (100 . "AcDbEntity") (8 . "ARCH") (62 . 7) (370 . 13) (100 . "AcDbLine") (10 4140.2714932127
2703.6199095023 0.0) (11 6685.520361991 2703.6199095023 0.0))
((0 . "LINE") (100 . "AcDbEntity") (8 . "ARCH") (62 . 7) (370 . 13) (100 . "AcDbLine") (10 6685.520361991
2703.6199095023 0.0) (11 6696.8325791855 2748.8687782805 0.0))
((0 . "LINE") (100 . "AcDbEntity") (8 . "ARCH") (62 . 7) (370 . 13) (100 . "AcDbLine") (10 6696.8325791855
2748.8687782805 0.0) (11 6708.1447963801 2794.1176470588 0.0))
((0 . "LINE") (100 . "AcDbEntity") (8 . "ARCH") (62 . 7) (370 . 13) (100 . "AcDbLine") (10 6708.1447963801
2794.1176470588 0.0) (11 6764.7058823529 2861.9909502262 0.0))
((0 . "LINE") (100 . "AcDbEntity") (8 . "ARCH") (62 . 7) (370 . 13) (100 . "AcDbLine") (10 4128.9592760181
2748.8687782805 0.0) (11 6696.8325791855 2748.8687782805 0.0))
((0 . "LINE") (100 . "AcDbEntity") (8 . "ARCH") (62 . 7) (370 . 13) (100 . "AcDbLine") (10 6705.3167420814
938.9140271493 0.0) (11 6719.4570135747 938.9140271493 0.0))
((0 . "LINE") (100 . "AcDbEntity") (8 . "ARCH") (62 . 7) (370 . 13) (100 . "AcDbLine") (10 6719.4570135747
938.9140271493 0.0) (11 6719.4570135747 859.7285067873 0.0))
((0 . "LINE") (100 . "AcDbEntity") (8 . "ARCH") (62 . 7) (370 . 13) (100 . "AcDbLine") (10 6719.4570135747
859.7285067873 0.0) (11 6651.5837104072 859.7285067873 0.0))
((0 . "LINE") (100 . "AcDbEntity") (8 . "ARCH") (62 . 7) (370 . 13) (100 . "AcDbLine") (10 6651.5837104072
859.7285067873 0.0) (11 4208.1447963801 859.7285067873 0.0))
((0 . "LINE") (100 . "AcDbEntity") (8 . "ARCH") (62 . 7) (370 . 13) (100 . "AcDbLine") (10 4208.1447963801
859.7285067873 0.0) (11 4140.2714932127 859.7285067873 0.0))
((0 . "LINE") (100 . "AcDbEntity") (8 . "ARCH") (62 . 7) (370 . 13) (100 . "AcDbLine") (10 4140.2714932127
859.7285067873 0.0) (11 4140.2714932127 935.1432918552 0.0))
((0 . "LINE") (100 . "AcDbEntity") (8 . "ARCH") (62 . 7) (370 . 13) (100 . "AcDbLine") (10 6651.5837104072
859.7285067873 0.0) (11 6651.5837104072 599.5475113122 0.0))
((0 . "LINE") (100 . "AcDbEntity") (8 . "ARCH") (62 . 7) (370 . 13) (100 . "AcDbLine") (10 6651.5837104072
599.5475113122 0.0) (11 4208.1447963801 599.5475113122 0.0))
((0 . "LINE") (100 . "AcDbEntity") (8 . "ARCH") (62 . 7) (370 . 13) (100 . "AcDbLine") (10 4208.1447963801
599.5475113122 0.0) (11 4208.1447963801 859.7285067873 0.0))
((0 . "LINE") (100 . "AcDbEntity") (8 . "ARCH") (62 . 7) (370 . 13) (100 . "AcDbLine") (10 4208.1447963801
576.9230769231 0.0) (11 5995.4751131222 576.9230769231 0.0))
((0 . "LINE") (100 . "AcDbEntity") (8 . "ARCH") (62 . 7) (370 . 13) (100 . "AcDbLine") (10 5995.4751131222
576.9230769231 0.0) (11 6651.5837104072 576.9230769231 0.0))
((0 . "LINE") (100 . "AcDbEntity") (8 . "ARCH") (62 . 7) (370 . 13) (100 . "AcDbLine") (10 3404.9773755656
3382.3529411765 0.0) (11 3529.4117647059 3382.3529411765 0.0))
((0 . "LINE") (100 . "AcDbEntity") (8 . "ARCH") (62 . 7) (370 . 13) (100 . "AcDbLine") (10 3529.4117647059
3382.3529411765 0.0) (11 3529.4117647059 2533.9366515837 0.0))
((0 . "LINE") (100 . "AcDbEntity") (8 . "ARCH") (62 . 7) (370 . 13) (100 . "AcDbLine") (10 3529.4117647059
2533.9366515837 0.0) (11 3404.9773755656 2533.9366515837 0.0))
((0 . "LINE") (100 . "AcDbEntity") (8 . "ARCH") (62 . 7) (370 . 13) (100 . "AcDbLine") (10 3404.9773755656
2533.9366515837 0.0) (11 3404.9773755656 3382.3529411765 0.0))
((0 . "LINE") (100 . "AcDbEntity") (8 . "ARCH") (62 . 7) (370 . 13) (100 . "AcDbLine") (10 3438.9140271493
3337.1040723982 0.0) (11 3495.4751131222 3337.1040723982 0.0))
((0 . "LINE") (100 . "AcDbEntity") (8 . "ARCH") (62 . 7) (370 . 13) (100 . "AcDbLine") (10 3495.4751131222
3337.1040723982 0.0) (11 3495.4751131222 2590.4977375566 0.0))
((0 . "LINE") (100 . "AcDbEntity") (8 . "ARCH") (62 . 7) (370 . 13) (100 . "AcDbLine") (10 3495.4751131222
2590.4977375566 0.0) (11 3438.9140271493 2590.4977375566 0.0))
((0 . "LINE") (100 . "AcDbEntity") (8 . "ARCH") (62 . 7) (370 . 13) (100 . "AcDbLine") (10 3438.9140271493
2590.4977375566 0.0) (11 3438.9140271493 3337.1040723982 0.0))
((0 . "LINE") (100 . "AcDbEntity") (8 . "ARCH") (62 . 7) (370 . 13) (100 . "AcDbLine") (10 7273.7556561086
3382.3529411765 0.0) (11 7398.1900452489 3382.3529411765 0.0))
((0 . "LINE") (100 . "AcDbEntity") (8 . "ARCH") (62 . 7) (370 . 13) (100 . "AcDbLine") (10 7398.1900452489
3382.3529411765 0.0) (11 7398.1900452489 2533.9366515837 0.0))
((0 . "LINE") (100 . "AcDbEntity") (8 . "ARCH") (62 . 7) (370 . 13) (100 . "AcDbLine") (10 7398.1900452489
2533.9366515837 0.0) (11 7273.7556561086 2533.9366515837 0.0))
((0 . "LINE") (100 . "AcDbEntity") (8 . "ARCH") (62 . 7) (370 . 13) (100 . "AcDbLine") (10 7273.7556561086
2533.9366515837 0.0) (11 7273.7556561086 3382.3529411765 0.0))
((0 . "LINE") (100 . "AcDbEntity") (8 . "ARCH") (62 . 7) (370 . 13) (100 . "AcDbLine") (10 7307.6923076923
3337.1040723982 0.0) (11 7364.2533936652 3337.1040723982 0.0))
((0 . "LINE") (100 . "AcDbEntity") (8 . "ARCH") (62 . 7) (370 . 13) (100 . "AcDbLine") (10 7364.2533936652
3337.1040723982 0.0) (11 7364.2533936652 2590.4977375566 0.0))
((0 . "LINE") (100 . "AcDbEntity") (8 . "ARCH") (62 . 7) (370 . 13) (100 . "AcDbLine") (10 7364.2533936652
2590.4977375566 0.0) (11 7307.6923076923 2590.4977375566 0.0))
((0 . "LINE") (100 . "AcDbEntity") (8 . "ARCH") (62 . 7) (370 . 13) (100 . "AcDbLine") (10 7307.6923076923
2590.4977375566 0.0) (11 7307.6923076923 3337.1040723982 0.0))
((0 . "LINE") (100 . "AcDbEntity") (8 . "ARCH") (62 . 7) (370 . 13) (100 . "AcDbLine") (10 13156.1085972851
5916.2895927602 0.0) (11 13359.7285067873 6052.036199095 0.0))
((0 . "LINE") (100 . "AcDbEntity") (8 . "ARCH") (62 . 7) (370 . 13) (100 . "AcDbLine") (10 13359.7285067873
6052.036199095 0.0) (11 15757.9185520362 6052.036199095 0.0))
((0 . "LINE") (100 . "AcDbEntity") (8 . "ARCH") (62 . 7) (370 . 13) (100 . "AcDbLine") (10 15757.9185520362
6052.036199095 0.0) (11 15995.4751131222 5916.2895927602 0.0))
((0 . "LINE") (100 . "AcDbEntity") (8 . "ARCH") (62 . 7) (370 . 13) (100 . "AcDbLine") (10 13156.1085972851
5916.2895927602 0.0) (11 15995.4751131222 5916.2895927602 0.0))
((0 . "LINE") (100 . "AcDbEntity") (8 . "ARCH") (62 . 7) (370 . 13) (100 . "AcDbLine") (10 15995.4751131222
5916.2895927602 0.0) (11 15995.4751131222 5848.4162895928 0.0))
((0 . "LINE") (100 . "AcDbEntity") (8 . "ARCH") (62 . 7) (370 . 13) (100 . "AcDbLine") (10 15995.4751131222
5848.4162895928 0.0) (11 13156.1085972851 5848.4162895928 0.0))
((0 . "LINE") (100 . "AcDbEntity") (8 . "ARCH") (62 . 7) (370 . 13) (100 . "AcDbLine") (10 13156.1085972851
5848.4162895928 0.0) (11 13156.1085972851 5916.2895927602 0.0))
((0 . "LINE") (100 . "AcDbEntity") (8 . "ARCH") (62 . 7) (370 . 13) (100 . "AcDbLine") (10 13156.1085972851
5848.4162895928 0.0) (11 13156.1085972851 5814.4796380091 0.0))
((0 . "LINE") (100 . "AcDbEntity") (8 . "ARCH") (62 . 7) (370 . 13) (100 . "AcDbLine") (10 13156.1085972851
5814.4796380091 0.0) (11 13156.1085972851 5791.8552036199 0.0))
((0 . "LINE") (100 . "AcDbEntity") (8 . "ARCH") (62 . 7) (370 . 13) (100 . "AcDbLine") (10 13156.1085972851
5791.8552036199 0.0) (11 13235.2941176471 5757.9185520362 0.0))
((0 . "LINE") (100 . "AcDbEntity") (8 . "ARCH") (62 . 7) (370 . 13) (100 . "AcDbLine") (10 13235.2941176471
5757.9185520362 0.0) (11 15904.9773755656 5757.9185520362 0.0))
((0 . "LINE") (100 . "AcDbEntity") (8 . "ARCH") (62 . 7) (370 . 13) (100 . "AcDbLine") (10 15904.9773755656
5757.9185520362 0.0) (11 15995.4751131222 5791.8552036199 0.0))
((0 . "LINE") (100 . "AcDbEntity") (8 . "ARCH") (62 . 7) (370 . 13) (100 . "AcDbLine") (10 15995.4751131222
5791.8552036199 0.0) (11 15995.4751131222 5814.4796380091 0.0))
((0 . "LINE") (100 . "AcDbEntity") (8 . "ARCH") (62 . 7) (370 . 13) (100 . "AcDbLine") (10 15995.4751131222
5814.4796380091 0.0) (11 15995.4751131222 5848.4162895928 0.0))
((0 . "LINE") (100 . "AcDbEntity") (8 . "ARCH") (62 . 7) (370 . 13) (100 . "AcDbLine") (10 13190.0452488688
5757.9185520362 0.0) (11 13235.2941176471 5757.9185520362 0.0))
((0 . "LINE") (100 . "AcDbEntity") (8 . "ARCH") (62 . 7) (370 . 13) (100 . "AcDbLine") (10 15904.9773755656
5757.9185520362 0.0) (11 15938.9140271493 5757.9185520362 0.0))
((0 . "LINE") (100 . "AcDbEntity") (8 . "ARCH") (62 . 7) (370 . 13) (100 . "AcDbLine") (10 15938.9140271493
5757.9185520362 0.0) (11 15938.9140271493 5746.6063348416 0.0))
((0 . "LINE") (100 . "AcDbEntity") (8 . "ARCH") (62 . 7) (370 . 13) (100 . "AcDbLine") (10 15938.9140271493
5746.6063348416 0.0) (11 15938.9140271493 5701.3574660633 0.0))
((0 . "LINE") (100 . "AcDbEntity") (8 . "ARCH") (62 . 7) (370 . 13) (100 . "AcDbLine") (10 15938.9140271493
5701.3574660633 0.0) (11 15859.7285067873 5701.3574660633 0.0))
((0 . "LINE") (100 . "AcDbEntity") (8 . "ARCH") (62 . 7) (370 . 13) (100 . "AcDbLine") (10 15859.7285067873
5701.3574660633 0.0) (11 13291.8552036199 5701.3574660633 0.0))
((0 . "LINE") (100 . "AcDbEntity") (8 . "ARCH") (62 . 7) (370 . 13) (100 . "AcDbLine") (10 13291.8552036199
5701.3574660633 0.0) (11 13190.0452488688 5701.3574660633 0.0))
((0 . "LINE") (100 . "AcDbEntity") (8 . "ARCH") (62 . 7) (370 . 13) (100 . "AcDbLine") (10 13190.0452488688
5701.3574660633 0.0) (11 13190.0452488688 5746.6063348416 0.0))
((0 . "LINE") (100 . "AcDbEntity") (8 . "ARCH") (62 . 7) (370 . 13) (100 . "AcDbLine") (10 13190.0452488688
5746.6063348416 0.0) (11 13190.0452488688 5757.9185520362 0.0))
((0 . "LINE") (100 . "AcDbEntity") (8 . "ARCH") (62 . 7) (370 . 13) (100 . "AcDbLine") (10 15859.7285067873
5701.3574660633 0.0) (11 15859.7285067873 5656.1085972851 0.0))
((0 . "LINE") (100 . "AcDbEntity") (8 . "ARCH") (62 . 7) (370 . 13) (100 . "AcDbLine") (10 15859.7285067873
5656.1085972851 0.0) (11 15825.7918552036 5622.1719457014 0.0))
((0 . "LINE") (100 . "AcDbEntity") (8 . "ARCH") (62 . 7) (370 . 13) (100 . "AcDbLine") (10 15825.7918552036
5622.1719457014 0.0) (11 15825.7918552036 5588.2352941176 0.0))
((0 . "LINE") (100 . "AcDbEntity") (8 . "ARCH") (62 . 7) (370 . 13) (100 . "AcDbLine") (10 15825.7918552036
5588.2352941176 0.0) (11 15825.7918552036 5576.9230769231 0.0))
((0 . "LINE") (100 . "AcDbEntity") (8 . "ARCH") (62 . 7) (370 . 13) (100 . "AcDbLine") (10 15825.7918552036
5576.9230769231 0.0) (11 13314.4796380091 5576.9230769231 0.0))
((0 . "LINE") (100 . "AcDbEntity") (8 . "ARCH") (62 . 7) (370 . 13) (100 . "AcDbLine") (10 13314.4796380091
5576.9230769231 0.0) (11 13314.4796380091 5588.2352941176 0.0))
((0 . "LINE") (100 . "AcDbEntity") (8 . "ARCH") (62 . 7) (370 . 13) (100 . "AcDbLine") (10 13314.4796380091
5588.2352941176 0.0) (11 13314.4796380091 5610.8597285068 0.0))
((0 . "LINE") (100 . "AcDbEntity") (8 . "ARCH") (62 . 7) (370 . 13) (100 . "AcDbLine") (10 13314.4796380091
5610.8597285068 0.0) (11 13314.4796380091 5622.1719457014 0.0))
((0 . "LINE") (100 . "AcDbEntity") (8 . "ARCH") (62 . 7) (370 . 13) (100 . "AcDbLine") (10 13314.4796380091
5622.1719457014 0.0) (11 13291.8552036199 5656.1085972851 0.0))
((0 . "LINE") (100 . "AcDbEntity") (8 . "ARCH") (62 . 7) (370 . 13) (100 . "AcDbLine") (10 13291.8552036199
5656.1085972851 0.0) (11 13291.8552036199 5701.3574660633 0.0))
((0 . "LINE") (100 . "AcDbEntity") (8 . "LOUVERS") (62 . 7) (370 . 13) (100 . "AcDbLine") (10 13325.7918552036
5531.6742081448 0.0) (11 13326.334841629 5531.6742081448 0.0))
((0 . "LINE") (100 . "AcDbEntity") (8 . "LOUVERS") (62 . 7) (370 . 13) (100 . "AcDbLine") (10 13326.334841629
5531.6742081448 0.0) (11 13386.9230769231 5531.6742081448 0.0))
((0 . "LINE") (100 . "AcDbEntity") (8 . "ARCH") (62 . 7) (370 . 13) (100 . "AcDbLine") (10 13386.9230769231
5531.6742081448 0.0) (11 13464.7850678733 5531.6742081448 0.0))
((0 . "LINE") (100 . "AcDbEntity") (8 . "ARCH") (62 . 7) (370 . 13) (100 . "AcDbLine") (10 13464.7850678733
5531.6742081448 0.0) (11 13480.4524886878 5531.6742081448 0.0))
((0 . "LINE") (100 . "AcDbEntity") (8 . "ARCH") (62 . 7) (370 . 13) (100 . "AcDbLine") (10 13480.4524886878
5531.6742081448 0.0) (11 13543.5520361991 5531.6742081448 0.0))
((0 . "LINE") (100 . "AcDbEntity") (8 . "ARCH") (62 . 7) (370 . 13) (100 . "AcDbLine") (10 13543.5520361991
5531.6742081448 0.0) (11 13625.4524886878 5531.6742081448 0.0))
((0 . "LINE") (100 . "AcDbEntity") (8 . "ARCH") (62 . 7) (370 . 13) (100 . "AcDbLine") (10 13625.4524886878
5531.6742081448 0.0) (11 13690.9389140272 5531.6742081448 0.0))
((0 . "LINE") (100 . "AcDbEntity") (8 . "ARCH") (62 . 7) (370 . 13) (100 . "AcDbLine") (10 13690.9389140272
5531.6742081448 0.0) (11 13707.8959276018 5531.6742081448 0.0))
((0 . "LINE") (100 . "AcDbEntity") (8 . "ARCH") (62 . 7) (370 . 13) (100 . "AcDbLine") (10 13707.8959276018
5531.6742081448 0.0) (11 13772.3755656109 5531.6742081448 0.0))
((0 . "LINE") (100 . "AcDbEntity") (8 . "ARCH") (62 . 7) (370 . 13) (100 . "AcDbLine") (10 13772.3755656109
5531.6742081448 0.0) (11 13823.5294117647 5531.6742081448 0.0))
((0 . "LINE") (100 . "AcDbEntity") (8 . "ARCH") (62 . 7) (370 . 13) (100 . "AcDbLine") (10 13823.5294117647
5531.6742081448 0.0) (11 15361.9909502262 5531.6742081448 0.0))
((0 . "LINE") (100 . "AcDbEntity") (8 . "LOUVERS") (62 . 7) (370 . 13) (100 . "AcDbLine") (10 15361.9909502262
5531.6742081448 0.0) (11 15421.685520362 5531.6742081448 0.0))
((0 . "LINE") (100 . "AcDbEntity") (8 . "LOUVERS") (62 . 7) (370 . 13) (100 . "AcDbLine") (10 15421.685520362
5531.6742081448 0.0) (11 15438.7104072398 5531.6742081448 0.0))
((0 . "LINE") (100 . "AcDbEntity") (8 . "LOUVERS") (62 . 7) (370 . 13) (100 . "AcDbLine") (10 15438.7104072398
5531.6742081448 0.0) (11 15498.5972850679 5531.6742081448 0.0))
((0 . "LINE") (100 . "AcDbEntity") (8 . "LOUVERS") (62 . 7) (370 . 13) (100 . "AcDbLine") (10 15498.5972850679
5531.6742081448 0.0) (11 15516.2895927602 5531.6742081448 0.0))
((0 . "LINE") (100 . "AcDbEntity") (8 . "LOUVERS") (62 . 7) (370 . 13) (100 . "AcDbLine") (10 15516.2895927602
5531.6742081448 0.0) (11 15568.1674208145 5531.6742081448 0.0))
((0 . "LINE") (100 . "AcDbEntity") (8 . "LOUVERS") (62 . 7) (370 . 13) (100 . "AcDbLine") (10 15568.1674208145
5531.6742081448 0.0) (11 15618.9479638009 5531.6742081448 0.0))
((0 . "LINE") (100 . "AcDbEntity") (8 . "LOUVERS") (62 . 7) (370 . 13) (100 . "AcDbLine") (10 15618.9479638009
5531.6742081448 0.0) (11 15681.3461538462 5531.6742081448 0.0))
((0 . "LINE") (100 . "AcDbEntity") (8 . "LOUVERS") (62 . 7) (370 . 13) (100 . "AcDbLine") (10 15681.3461538462
5531.6742081448 0.0) (11 15698.7330316742 5531.6742081448 0.0))
((0 . "LINE") (100 . "AcDbEntity") (8 . "LOUVERS") (62 . 7) (370 . 13) (100 . "AcDbLine") (10 15698.7330316742
5531.6742081448 0.0) (11 15748.834841629 5531.6742081448 0.0))
((0 . "LINE") (100 . "AcDbEntity") (8 . "LOUVERS") (62 . 7) (370 . 13) (100 . "AcDbLine") (10 15748.834841629
5531.6742081448 0.0) (11 15775.2941176471 5531.6742081448 0.0))
((0 . "LINE") (100 . "AcDbEntity") (8 . "LOUVERS") (62 . 7) (370 . 13) (100 . "AcDbLine") (10 15775.2941176471
5531.6742081448 0.0) (11 15825.7918552036 5531.6742081448 0.0))
((0 . "LINE") (100 . "AcDbEntity") (8 . "ARCH") (62 . 7) (370 . 13) (100 . "AcDbLine") (10 13314.4796380091
5588.2352941176 0.0) (11 15825.7918552036 5588.2352941176 0.0))
((0 . "LINE") (100 . "AcDbEntity") (8 . "ARCH") (62 . 7) (370 . 13) (100 . "AcDbLine") (10 15825.7918552036
5588.2352941176 0.0) (11 15837.1040723982 5588.2352941176 0.0))
((0 . "LINE") (100 . "AcDbEntity") (8 . "ARCH") (62 . 7) (370 . 13) (100 . "AcDbLine") (10 15938.9140271493
3733.0316742081 0.0) (11 15938.9140271493 3721.7194570136 0.0))
((0 . "LINE") (100 . "AcDbEntity") (8 . "ARCH") (62 . 7) (370 . 13) (100 . "AcDbLine") (10 15938.9140271493
3721.7194570136 0.0) (11 15938.9140271493 3585.9728506787 0.0))
((0 . "LINE") (100 . "AcDbEntity") (8 . "ARCH") (62 . 7) (370 . 13) (100 . "AcDbLine") (10 15938.9140271493
3585.9728506787 0.0) (11 15938.9140271493 3235.2941176471 0.0))
((0 . "LINE") (100 . "AcDbEntity") (8 . "ARCH") (62 . 7) (370 . 13) (100 . "AcDbLine") (10 15938.9140271493
3235.2941176471 0.0) (11 15927.6018099548 3235.2941176471 0.0))
((0 . "LINE") (100 . "AcDbEntity") (8 . "ARCH") (62 . 7) (370 . 13) (100 . "AcDbLine") (10 15927.6018099548
3235.2941176471 0.0) (11 13614.2533936652 3235.2941176471 0.0))
((0 . "LINE") (100 . "AcDbEntity") (8 . "ARCH") (62 . 7) (370 . 13) (100 . "AcDbLine") (10 13512.443438914
3235.2941176471 0.0) (11 13201.3574660633 3235.2941176471 0.0))
((0 . "LINE") (100 . "AcDbEntity") (8 . "ARCH") (62 . 7) (370 . 13) (100 . "AcDbLine") (10 13201.3574660633
3235.2941176471 0.0) (11 13190.0452488688 3235.2941176471 0.0))
((0 . "LINE") (100 . "AcDbEntity") (8 . "ARCH") (62 . 7) (370 . 13) (100 . "AcDbLine") (10 13190.0452488688
3235.2941176471 0.0) (11 13190.0452488688 3585.9728506787 0.0))
((0 . "LINE") (100 . "AcDbEntity") (8 . "ARCH") (62 . 7) (370 . 13) (100 . "AcDbLine") (10 13190.0452488688
3585.9728506787 0.0) (11 13190.0452488688 3721.7194570136 0.0))
((0 . "LINE") (100 . "AcDbEntity") (8 . "ARCH") (62 . 7) (370 . 13) (100 . "AcDbLine") (10 13190.0452488688
3721.7194570136 0.0) (11 13190.0452488688 3733.0316742081 0.0))
((0 . "LINE") (100 . "AcDbEntity") (8 . "ARCH") (62 . 7) (370 . 13) (100 . "AcDbLine") (10 15927.6018099548
3235.2941176471 0.0) (11 15927.6018099548 2941.1764705882 0.0))
((0 . "LINE") (100 . "AcDbEntity") (8 . "ARCH") (62 . 7) (370 . 13) (100 . "AcDbLine") (10 15927.6018099548
2941.1764705882 0.0) (11 13201.3574660633 2941.1764705882 0.0))
((0 . "LINE") (100 . "AcDbEntity") (8 . "ARCH") (62 . 7) (370 . 13) (100 . "AcDbLine") (10 13201.3574660633
2941.1764705882 0.0) (11 13201.3574660633 3235.2941176471 0.0))
((0 . "LINE") (100 . "AcDbEntity") (8 . "ARCH") (62 . 7) (370 . 13) (100 . "AcDbLine") (10 13178.7330316742
2941.1764705882 0.0) (11 13201.3574660633 2941.1764705882 0.0))
((0 . "LINE") (100 . "AcDbEntity") (8 . "ARCH") (62 . 7) (370 . 13) (100 . "AcDbLine") (10 15927.6018099548
2941.1764705882 0.0) (11 15938.9140271493 2941.1764705882 0.0))
((0 . "LINE") (100 . "AcDbEntity") (8 . "ARCH") (62 . 7) (370 . 13) (100 . "AcDbLine") (10 15938.9140271493
2941.1764705882 0.0) (11 15938.9140271493 2861.9909502262 0.0))
((0 . "LINE") (100 . "AcDbEntity") (8 . "ARCH") (62 . 7) (370 . 13) (100 . "AcDbLine") (10 15938.9140271493
2861.9909502262 0.0) (11 15916.2895927602 2861.9909502262 0.0))
((0 . "LINE") (100 . "AcDbEntity") (8 . "ARCH") (62 . 7) (370 . 13) (100 . "AcDbLine") (10 15916.2895927602
2861.9909502262 0.0) (11 13201.3574660633 2861.9909502262 0.0))
((0 . "LINE") (100 . "AcDbEntity") (8 . "ARCH") (62 . 7) (370 . 13) (100 . "AcDbLine") (10 13201.3574660633
2861.9909502262 0.0) (11 13178.7330316742 2861.9909502262 0.0))
((0 . "LINE") (100 . "AcDbEntity") (8 . "ARCH") (62 . 7) (370 . 13) (100 . "AcDbLine") (10 13178.7330316742
2861.9909502262 0.0) (11 13178.7330316742 2941.1764705882 0.0))
((0 . "LINE") (100 . "AcDbEntity") (8 . "ARCH") (62 . 7) (370 . 13) (100 . "AcDbLine") (10 13201.3574660633
2861.9909502262 0.0) (11 13269.2307692308 2794.1176470588 0.0))
((0 . "LINE") (100 . "AcDbEntity") (8 . "ARCH") (62 . 7) (370 . 13) (100 . "AcDbLine") (10 13269.2307692308
2794.1176470588 0.0) (11 13280.5429864253 2748.8687782805 0.0))
((0 . "LINE") (100 . "AcDbEntity") (8 . "ARCH") (62 . 7) (370 . 13) (100 . "AcDbLine") (10 13280.5429864253
2748.8687782805 0.0) (11 13291.8552036199 2703.6199095023 0.0))
((0 . "LINE") (100 . "AcDbEntity") (8 . "ARCH") (62 . 7) (370 . 13) (100 . "AcDbLine") (10 13291.8552036199
2703.6199095023 0.0) (11 15837.1040723982 2703.6199095023 0.0))
((0 . "LINE") (100 . "AcDbEntity") (8 . "ARCH") (62 . 7) (370 . 13) (100 . "AcDbLine") (10 15837.1040723982
2703.6199095023 0.0) (11 15848.4162895928 2748.8687782805 0.0))
((0 . "LINE") (100 . "AcDbEntity") (8 . "ARCH") (62 . 7) (370 . 13) (100 . "AcDbLine") (10 15848.4162895928
2748.8687782805 0.0) (11 15859.7285067873 2794.1176470588 0.0))
((0 . "LINE") (100 . "AcDbEntity") (8 . "ARCH") (62 . 7) (370 . 13) (100 . "AcDbLine") (10 15859.7285067873
2794.1176470588 0.0) (11 15916.2895927602 2861.9909502262 0.0))
((0 . "LINE") (100 . "AcDbEntity") (8 . "ARCH") (62 . 7) (370 . 13) (100 . "AcDbLine") (10 13280.5429864253
2748.8687782805 0.0) (11 15848.4162895928 2748.8687782805 0.0))
((0 . "LINE") (100 . "AcDbEntity") (8 . "ARCH") (62 . 7) (370 . 13) (100 . "AcDbLine") (10 15856.9004524887
938.9140271493 0.0) (11 15871.0407239819 938.9140271493 0.0))
((0 . "LINE") (100 . "AcDbEntity") (8 . "ARCH") (62 . 7) (370 . 13) (100 . "AcDbLine") (10 15871.0407239819
938.9140271493 0.0) (11 15871.0407239819 859.7285067873 0.0))
((0 . "LINE") (100 . "AcDbEntity") (8 . "ARCH") (62 . 7) (370 . 13) (100 . "AcDbLine") (10 15871.0407239819
859.7285067873 0.0) (11 15803.1674208145 859.7285067873 0.0))
((0 . "LINE") (100 . "AcDbEntity") (8 . "ARCH") (62 . 7) (370 . 13) (100 . "AcDbLine") (10 15803.1674208145
859.7285067873 0.0) (11 13359.7285067873 859.7285067873 0.0))
((0 . "LINE") (100 . "AcDbEntity") (8 . "ARCH") (62 . 7) (370 . 13) (100 . "AcDbLine") (10 13359.7285067873
859.7285067873 0.0) (11 13291.8552036199 859.7285067873 0.0))
((0 . "LINE") (100 . "AcDbEntity") (8 . "ARCH") (62 . 7) (370 . 13) (100 . "AcDbLine") (10 13291.8552036199
859.7285067873 0.0) (11 13291.8552036199 935.1432918552 0.0))
((0 . "LINE") (100 . "AcDbEntity") (8 . "ARCH") (62 . 7) (370 . 13) (100 . "AcDbLine") (10 15803.1674208145
859.7285067873 0.0) (11 15803.1674208145 599.5475113122 0.0))
((0 . "LINE") (100 . "AcDbEntity") (8 . "ARCH") (62 . 7) (370 . 13) (100 . "AcDbLine") (10 15803.1674208145
599.5475113122 0.0) (11 13359.7285067873 599.5475113122 0.0))
((0 . "LINE") (100 . "AcDbEntity") (8 . "ARCH") (62 . 7) (370 . 13) (100 . "AcDbLine") (10 13359.7285067873
599.5475113122 0.0) (11 13359.7285067873 859.7285067873 0.0))
((0 . "LINE") (100 . "AcDbEntity") (8 . "ARCH") (62 . 7) (370 . 13) (100 . "AcDbLine") (10 13359.7285067873
576.9230769231 0.0) (11 15339.3665158371 576.9230769231 0.0))
((0 . "LINE") (100 . "AcDbEntity") (8 . "ARCH") (62 . 7) (370 . 13) (100 . "AcDbLine") (10 15339.3665158371
576.9230769231 0.0) (11 15803.1674208145 576.9230769231 0.0))
((0 . "LINE") (100 . "AcDbEntity") (8 . "ARCH") (62 . 7) (370 . 13) (100 . "AcDbLine") (10 12601.8099547511
3382.3529411765 0.0) (11 12726.2443438914 3382.3529411765 0.0))
((0 . "LINE") (100 . "AcDbEntity") (8 . "ARCH") (62 . 7) (370 . 13) (100 . "AcDbLine") (10 12726.2443438914
3382.3529411765 0.0) (11 12726.2443438914 2533.9366515837 0.0))
((0 . "LINE") (100 . "AcDbEntity") (8 . "ARCH") (62 . 7) (370 . 13) (100 . "AcDbLine") (10 12726.2443438914
2533.9366515837 0.0) (11 12601.8099547511 2533.9366515837 0.0))
((0 . "LINE") (100 . "AcDbEntity") (8 . "ARCH") (62 . 7) (370 . 13) (100 . "AcDbLine") (10 12601.8099547511
2533.9366515837 0.0) (11 12601.8099547511 3382.3529411765 0.0))
((0 . "LINE") (100 . "AcDbEntity") (8 . "ARCH") (62 . 7) (370 . 13) (100 . "AcDbLine") (10 12635.7466063348
3337.1040723982 0.0) (11 12692.3076923077 3337.1040723982 0.0))
((0 . "LINE") (100 . "AcDbEntity") (8 . "ARCH") (62 . 7) (370 . 13) (100 . "AcDbLine") (10 12692.3076923077
3337.1040723982 0.0) (11 12692.3076923077 2590.4977375566 0.0))
((0 . "LINE") (100 . "AcDbEntity") (8 . "ARCH") (62 . 7) (370 . 13) (100 . "AcDbLine") (10 12692.3076923077
2590.4977375566 0.0) (11 12635.7466063348 2590.4977375566 0.0))
((0 . "LINE") (100 . "AcDbEntity") (8 . "ARCH") (62 . 7) (370 . 13) (100 . "AcDbLine") (10 12635.7466063348
2590.4977375566 0.0) (11 12635.7466063348 3337.1040723982 0.0))
((0 . "LINE") (100 . "AcDbEntity") (8 . "ARCH") (62 . 7) (370 . 13) (100 . "AcDbLine") (10 16481.9004524887
3382.3529411765 0.0) (11 16606.334841629 3382.3529411765 0.0))
((0 . "LINE") (100 . "AcDbEntity") (8 . "ARCH") (62 . 7) (370 . 13) (100 . "AcDbLine") (10 16606.334841629
3382.3529411765 0.0) (11 16606.334841629 2533.9366515837 0.0))
((0 . "LINE") (100 . "AcDbEntity") (8 . "ARCH") (62 . 7) (370 . 13) (100 . "AcDbLine") (10 16606.334841629
2533.9366515837 0.0) (11 16481.9004524887 2533.9366515837 0.0))
((0 . "LINE") (100 . "AcDbEntity") (8 . "ARCH") (62 . 7) (370 . 13) (100 . "AcDbLine") (10 16481.9004524887
2533.9366515837 0.0) (11 16481.9004524887 3382.3529411765 0.0))
((0 . "LINE") (100 . "AcDbEntity") (8 . "ARCH") (62 . 7) (370 . 13) (100 . "AcDbLine") (10 16515.8371040724
3337.1040723982 0.0) (11 16572.3981900452 3337.1040723982 0.0))
((0 . "LINE") (100 . "AcDbEntity") (8 . "ARCH") (62 . 7) (370 . 13) (100 . "AcDbLine") (10 16572.3981900452
3337.1040723982 0.0) (11 16572.3981900452 2590.4977375566 0.0))
((0 . "LINE") (100 . "AcDbEntity") (8 . "ARCH") (62 . 7) (370 . 13) (100 . "AcDbLine") (10 16572.3981900452
2590.4977375566 0.0) (11 16515.8371040724 2590.4977375566 0.0))
((0 . "LINE") (100 . "AcDbEntity") (8 . "ARCH") (62 . 7) (370 . 13) (100 . "AcDbLine") (10 16515.8371040724
2590.4977375566 0.0) (11 16515.8371040724 3337.1040723982 0.0))
((0 . "LINE") (100 . "AcDbEntity") (8 . "ARCH") (62 . 7) (370 . 13) (100 . "AcDbLine") (10 2398.1900452489
3744.3438914027 0.0) (11 2398.1900452489 3303.1674208145 0.0))
((0 . "LINE") (100 . "AcDbEntity") (8 . "ARCH") (62 . 7) (370 . 13) (100 . "AcDbLine") (10 2398.1900452489
3303.1674208145 0.0) (11 2398.1900452489 3280.5429864253 0.0))
((0 . "LINE") (100 . "AcDbEntity") (8 . "ARCH") (62 . 7) (370 . 13) (100 . "AcDbLine") (10 2398.1900452489
3280.5429864253 0.0) (11 2263.3716176471 3280.5429864253 0.0))
((0 . "LINE") (100 . "AcDbEntity") (8 . "ARCH") (62 . 7) (370 . 13) (100 . "AcDbLine") (10 2080.5197850679
3280.5429864253 0.0) (11 1097.1195248869 3280.5429864253 0.0))
((0 . "LINE") (100 . "AcDbEntity") (8 . "ARCH") (62 . 7) (370 . 13) (100 . "AcDbLine") (10 2352.9411764706
3744.3438914027 0.0) (11 2352.9411764706 3694.7171945701 0.0))
((0 . "LINE") (100 . "AcDbEntity") (8 . "ARCH") (62 . 7) (370 . 13) (100 . "AcDbLine") (10 2352.9411764706
3694.7171945701 0.0) (11 2352.9411764706 3654.5248868778 0.0))
((0 . "LINE") (100 . "AcDbEntity") (8 . "ARCH") (62 . 7) (370 . 13) (100 . "AcDbLine") (10 2352.9411764706
3654.5248868778 0.0) (11 2352.9411764706 3628.1108597285 0.0))
((0 . "LINE") (100 . "AcDbEntity") (8 . "ARCH") (62 . 7) (370 . 13) (100 . "AcDbLine") (10 2352.9411764706
3628.1108597285 0.0) (11 2352.9411764706 3590.8597285068 0.0))
((0 . "LINE") (100 . "AcDbEntity") (8 . "ARCH") (62 . 7) (370 . 13) (100 . "AcDbLine") (10 2352.9411764706
3590.8597285068 0.0) (11 2352.9411764706 3538.5180995475 0.0))
((0 . "LINE") (100 . "AcDbEntity") (8 . "ARCH") (62 . 7) (370 . 13) (100 . "AcDbLine") (10 2352.9411764706
3538.5180995475 0.0) (11 2352.9411764706 3476.8778280543 0.0))
((0 . "LINE") (100 . "AcDbEntity") (8 . "ARCH") (62 . 7) (370 . 13) (100 . "AcDbLine") (10 2352.9411764706
3476.8778280543 0.0) (11 2352.9411764706 3437.149321267 0.0))
((0 . "LINE") (100 . "AcDbEntity") (8 . "ARCH") (62 . 7) (370 . 13) (100 . "AcDbLine") (10 2352.9411764706
3437.149321267 0.0) (11 2352.9411764706 3405.6900452489 0.0))
((0 . "LINE") (100 . "AcDbEntity") (8 . "ARCH") (62 . 7) (370 . 13) (100 . "AcDbLine") (10 2352.9411764706
3405.6900452489 0.0) (11 2352.9411764706 3371.2669683258 0.0))
((0 . "LINE") (100 . "AcDbEntity") (8 . "ARCH") (62 . 7) (370 . 13) (100 . "AcDbLine") (10 2352.9411764706
3371.2669683258 0.0) (11 2352.9411764706 3303.1674208145 0.0))
((0 . "LINE") (100 . "AcDbEntity") (8 . "ARCH") (62 . 7) (370 . 13) (100 . "AcDbLine") (10 1148.5554524887
3694.7171945701 0.0) (11 2007.5430769231 3694.7171945701 0.0))
((0 . "LINE") (100 . "AcDbEntity") (8 . "ARCH") (62 . 7) (370 . 13) (100 . "AcDbLine") (10 2336.3483257919
3694.7171945701 0.0) (11 2352.9411764706 3694.7171945701 0.0))
((0 . "LINE") (100 . "AcDbEntity") (8 . "ARCH") (62 . 7) (370 . 13) (100 . "AcDbLine") (10 1145.3471945701
3654.5248868778 0.0) (11 2011.1407126697 3654.5248868778 0.0))
((0 . "LINE") (100 . "AcDbEntity") (8 . "ARCH") (62 . 7) (370 . 13) (100 . "AcDbLine") (10 2332.7506900452
3654.5248868778 0.0) (11 2352.9411764706 3654.5248868778 0.0))
((0 . "LINE") (100 . "AcDbEntity") (8 . "ARCH") (62 . 7) (370 . 13) (100 . "AcDbLine") (10 1143.2387556561
3628.1108597285 0.0) (11 2013.5050452489 3628.1108597285 0.0))
((0 . "LINE") (100 . "AcDbEntity") (8 . "ARCH") (62 . 7) (370 . 13) (100 . "AcDbLine") (10 2330.3863574661
3628.1108597285 0.0) (11 2352.9411764706 3628.1108597285 0.0))
((0 . "LINE") (100 . "AcDbEntity") (8 . "ARCH") (62 . 7) (370 . 13) (100 . "AcDbLine") (10 1140.2652714932
3590.8597285068 0.0) (11 2016.8394117647 3590.8597285068 0.0))
((0 . "LINE") (100 . "AcDbEntity") (8 . "ARCH") (62 . 7) (370 . 13) (100 . "AcDbLine") (10 2327.0519909502
3590.8597285068 0.0) (11 2352.9411764706 3590.8597285068 0.0))
((0 . "LINE") (100 . "AcDbEntity") (8 . "ARCH") (62 . 7) (370 . 13) (100 . "AcDbLine") (10 1136.0872285068
3538.5180995475 0.0) (11 2021.5245361991 3538.5180995475 0.0))
((0 . "LINE") (100 . "AcDbEntity") (8 . "ARCH") (62 . 7) (370 . 13) (100 . "AcDbLine") (10 2322.3668665158
3538.5180995475 0.0) (11 2352.9411764706 3538.5180995475 0.0))
((0 . "LINE") (100 . "AcDbEntity") (8 . "ARCH") (62 . 7) (370 . 13) (100 . "AcDbLine") (10 1131.1669343891
3476.8778280543 0.0) (11 2027.0419909502 3476.8778280543 0.0))
((0 . "LINE") (100 . "AcDbEntity") (8 . "ARCH") (62 . 7) (370 . 13) (100 . "AcDbLine") (10 2316.8494117647
3476.8778280543 0.0) (11 2352.9411764706 3476.8778280543 0.0))
((0 . "LINE") (100 . "AcDbEntity") (8 . "ARCH") (62 . 7) (370 . 13) (100 . "AcDbLine") (10 1127.9957013575
3437.149321267 0.0) (11 2037.6872850679 3437.149321267 0.0))
((0 . "LINE") (100 . "AcDbEntity") (8 . "ARCH") (62 . 7) (370 . 13) (100 . "AcDbLine") (10 2306.2041176471
3437.149321267 0.0) (11 2352.9411764706 3437.149321267 0.0))
((0 . "LINE") (100 . "AcDbEntity") (8 . "ARCH") (62 . 7) (370 . 13) (100 . "AcDbLine") (10 1125.4845475113
3405.6900452489 0.0) (11 2046.2915271493 3405.6900452489 0.0))
((0 . "LINE") (100 . "AcDbEntity") (8 . "ARCH") (62 . 7) (370 . 13) (100 . "AcDbLine") (10 2297.5998755656
3405.6900452489 0.0) (11 2352.9411764706 3405.6900452489 0.0))
((0 . "LINE") (100 . "AcDbEntity") (8 . "ARCH") (62 . 7) (370 . 13) (100 . "AcDbLine") (10 1119.2473190045
3371.2669683258 0.0) (11 2055.7063800905 3371.2669683258 0.0))
((0 . "LINE") (100 . "AcDbEntity") (8 . "ARCH") (62 . 7) (370 . 13) (100 . "AcDbLine") (10 2288.1850226244
3371.2669683258 0.0) (11 2352.9411764706 3371.2669683258 0.0))
((0 . "LINE") (100 . "AcDbEntity") (8 . "ARCH") (62 . 7) (370 . 13) (100 . "AcDbLine") (10 1102.6376809955
3303.1674208145 0.0) (11 2074.3319004525 3303.1674208145 0.0))
((0 . "LINE") (100 . "AcDbEntity") (8 . "ARCH") (62 . 7) (370 . 13) (100 . "AcDbLine") (10 2269.5595022624
3303.1674208145 0.0) (11 2352.9411764706 3303.1674208145 0.0))
((0 . "LINE") (100 . "AcDbEntity") (8 . "ARCH") (62 . 7) (370 . 13) (100 . "AcDbLine") (10 2352.9411764706
3303.1674208145 0.0) (11 2398.1900452489 3303.1674208145 0.0))
((0 . "LINE") (100 . "AcDbEntity") (8 . "ARCH") (62 . 7) (370 . 13) (100 . "AcDbLine") (10 2398.1900452489
3303.1674208145 0.0) (11 2420.814479638 3303.1674208145 0.0))
((0 . "LINE") (100 . "AcDbEntity") (8 . "ARCH") (62 . 7) (370 . 13) (100 . "AcDbLine") (10 2533.9366515837
916.2895927602 0.0) (11 2533.9366515837 520.3619909502 0.0))
((0 . "LINE") (100 . "AcDbEntity") (8 . "ARCH") (62 . 7) (370 . 13) (100 . "AcDbLine") (10 2533.9366515837
520.3619909502 0.0) (11 2533.9366515837 497.7375565611 0.0))
((0 . "LINE") (100 . "AcDbEntity") (8 . "ARCH") (62 . 7) (370 . 13) (100 . "AcDbLine") (10 2533.9366515837
497.7375565611 0.0) (11 2275.7473755656 497.7375565611 0.0))
((0 . "LINE") (100 . "AcDbEntity") (8 . "ARCH") (62 . 7) (370 . 13) (100 . "AcDbLine") (10 2068.1440271493
497.7375565611 0.0) (11 1108.1558371041 497.7375565611 0.0))
((0 . "LINE") (100 . "AcDbEntity") (8 . "ARCH") (62 . 7) (370 . 13) (100 . "AcDbLine") (10 2488.6877828054
916.2895927602 0.0) (11 2488.6877828054 890.7126696833 0.0))
((0 . "LINE") (100 . "AcDbEntity") (8 . "ARCH") (62 . 7) (370 . 13) (100 . "AcDbLine") (10 2488.6877828054
890.7126696833 0.0) (11 2488.6877828054 856.7986425339 0.0))
((0 . "LINE") (100 . "AcDbEntity") (8 . "ARCH") (62 . 7) (370 . 13) (100 . "AcDbLine") (10 2488.6877828054
856.7986425339 0.0) (11 2488.6877828054 820.7013574661 0.0))
((0 . "LINE") (100 . "AcDbEntity") (8 . "ARCH") (62 . 7) (370 . 13) (100 . "AcDbLine") (10 2488.6877828054
820.7013574661 0.0) (11 2488.6877828054 756.3235294118 0.0))
((0 . "LINE") (100 . "AcDbEntity") (8 . "ARCH") (62 . 7) (370 . 13) (100 . "AcDbLine") (10 2488.6877828054
756.3235294118 0.0) (11 2488.6877828054 692.7375565611 0.0))
((0 . "LINE") (100 . "AcDbEntity") (8 . "ARCH") (62 . 7) (370 . 13) (100 . "AcDbLine") (10 2488.6877828054
692.7375565611 0.0) (11 2488.6877828054 634.3665158371 0.0))
((0 . "LINE") (100 . "AcDbEntity") (8 . "ARCH") (62 . 7) (370 . 13) (100 . "AcDbLine") (10 2488.6877828054
634.3665158371 0.0) (11 2488.6877828054 597.0022624434 0.0))
((0 . "LINE") (100 . "AcDbEntity") (8 . "ARCH") (62 . 7) (370 . 13) (100 . "AcDbLine") (10 2488.6877828054
597.0022624434 0.0) (11 2488.6877828054 575.3393665158 0.0))
((0 . "LINE") (100 . "AcDbEntity") (8 . "ARCH") (62 . 7) (370 . 13) (100 . "AcDbLine") (10 2488.6877828054
575.3393665158 0.0) (11 2488.6877828054 520.3619909502 0.0))
((0 . "LINE") (100 . "AcDbEntity") (8 . "ARCH") (62 . 7) (370 . 13) (100 . "AcDbLine") (10 1150.475158371 890.7126696833
0.0) (11 2005.3903733032 890.7126696833 0.0))
((0 . "LINE") (100 . "AcDbEntity") (8 . "ARCH") (62 . 7) (370 . 13) (100 . "AcDbLine") (10 2338.5010294118
890.7126696833 0.0) (11 2488.6877828054 890.7126696833 0.0))
((0 . "LINE") (100 . "AcDbEntity") (8 . "ARCH") (62 . 7) (370 . 13) (100 . "AcDbLine") (10 1147.7680542986
856.7986425339 0.0) (11 2008.426040724 856.7986425339 0.0))
((0 . "LINE") (100 . "AcDbEntity") (8 . "ARCH") (62 . 7) (370 . 13) (100 . "AcDbLine") (10 2335.465361991 856.7986425339
0.0) (11 2488.6877828054 856.7986425339 0.0))
((0 . "LINE") (100 . "AcDbEntity") (8 . "ARCH") (62 . 7) (370 . 13) (100 . "AcDbLine") (10 1144.8866742081
820.7013574661 0.0) (11 2011.6571266968 820.7013574661 0.0))
((0 . "LINE") (100 . "AcDbEntity") (8 . "ARCH") (62 . 7) (370 . 13) (100 . "AcDbLine") (10 2332.2342760181
820.7013574661 0.0) (11 2488.6877828054 820.7013574661 0.0))
((0 . "LINE") (100 . "AcDbEntity") (8 . "ARCH") (62 . 7) (370 . 13) (100 . "AcDbLine") (10 1139.7478733032
756.3235294118 0.0) (11 2017.4196153846 756.3235294118 0.0))
((0 . "LINE") (100 . "AcDbEntity") (8 . "ARCH") (62 . 7) (370 . 13) (100 . "AcDbLine") (10 2326.4717873303
756.3235294118 0.0) (11 2488.6877828054 756.3235294118 0.0))
((0 . "LINE") (100 . "AcDbEntity") (8 . "ARCH") (62 . 7) (370 . 13) (100 . "AcDbLine") (10 1134.6722737557
692.7375565611 0.0) (11 2023.1112217195 692.7375565611 0.0))
((0 . "LINE") (100 . "AcDbEntity") (8 . "ARCH") (62 . 7) (370 . 13) (100 . "AcDbLine") (10 2320.7801809955
692.7375565611 0.0) (11 2488.6877828054 692.7375565611 0.0))
((0 . "LINE") (100 . "AcDbEntity") (8 . "ARCH") (62 . 7) (370 . 13) (100 . "AcDbLine") (10 1130.0129411765
634.3665158371 0.0) (11 2030.775418552 634.3665158371 0.0))
((0 . "LINE") (100 . "AcDbEntity") (8 . "ARCH") (62 . 7) (370 . 13) (100 . "AcDbLine") (10 2313.1159841629
634.3665158371 0.0) (11 2488.6877828054 634.3665158371 0.0))
((0 . "LINE") (100 . "AcDbEntity") (8 . "ARCH") (62 . 7) (370 . 13) (100 . "AcDbLine") (10 1127.0304298643
597.0022624434 0.0) (11 2040.9947058824 597.0022624434 0.0))
((0 . "LINE") (100 . "AcDbEntity") (8 . "ARCH") (62 . 7) (370 . 13) (100 . "AcDbLine") (10 2302.8966968326
597.0022624434 0.0) (11 2488.6877828054 597.0022624434 0.0))
((0 . "LINE") (100 . "AcDbEntity") (8 . "ARCH") (62 . 7) (370 . 13) (100 . "AcDbLine") (10 1125.3012443439
575.3393665158 0.0) (11 2046.9195927602 575.3393665158 0.0))
((0 . "LINE") (100 . "AcDbEntity") (8 . "ARCH") (62 . 7) (370 . 13) (100 . "AcDbLine") (10 2296.9718099548
575.3393665158 0.0) (11 2488.6877828054 575.3393665158 0.0))
((0 . "LINE") (100 . "AcDbEntity") (8 . "ARCH") (62 . 7) (370 . 13) (100 . "AcDbLine") (10 1113.6739819005
520.3619909502 0.0) (11 2061.9561425339 520.3619909502 0.0))
((0 . "LINE") (100 . "AcDbEntity") (8 . "ARCH") (62 . 7) (370 . 13) (100 . "AcDbLine") (10 2281.935260181 520.3619909502
0.0) (11 2488.6877828054 520.3619909502 0.0))
((0 . "LINE") (100 . "AcDbEntity") (8 . "ARCH") (62 . 7) (370 . 13) (100 . "AcDbLine") (10 2488.6877828054
520.3619909502 0.0) (11 2533.9366515837 520.3619909502 0.0))
((0 . "LINE") (100 . "AcDbEntity") (8 . "ARCH") (62 . 7) (370 . 13) (100 . "AcDbLine") (10 2533.9366515837
520.3619909502 0.0) (11 2556.5610859729 520.3619909502 0.0))
((0 . "LINE") (100 . "AcDbEntity") (8 . "ARCH") (62 . 7) (370 . 13) (100 . "AcDbLine") (10 18932.272658371
3280.5429864253 0.0) (11 18881.0186764706 3280.5429864253 0.0))
((0 . "LINE") (100 . "AcDbEntity") (8 . "ARCH") (62 . 7) (370 . 13) (100 . "AcDbLine") (10 18698.1668438914
3280.5429864253 0.0) (11 17714.7665837104 3280.5429864253 0.0))
((0 . "LINE") (100 . "AcDbEntity") (8 . "ARCH") (62 . 7) (370 . 13) (100 . "AcDbLine") (10 17766.3108597285
3696.0746606335 0.0) (11 18625.0686312217 3696.0746606335 0.0))
((0 . "LINE") (100 . "AcDbEntity") (8 . "ARCH") (62 . 7) (370 . 13) (100 . "AcDbLine") (10 17762.9969570136
3654.5588235294 0.0) (11 18628.784739819 3654.5588235294 0.0))
((0 . "LINE") (100 . "AcDbEntity") (8 . "ARCH") (62 . 7) (370 . 13) (100 . "AcDbLine") (10 17760.5670701357
3624.1176470588 0.0) (11 18631.5095361991 3624.1176470588 0.0))
((0 . "LINE") (100 . "AcDbEntity") (8 . "ARCH") (62 . 7) (370 . 13) (100 . "AcDbLine") (10 17757.5899660633
3586.8212669683 0.0) (11 18634.8479524887 3586.8212669683 0.0))
((0 . "LINE") (100 . "AcDbEntity") (8 . "ARCH") (62 . 7) (370 . 13) (100 . "AcDbLine") (10 17753.6078733032
3536.9343891403 0.0) (11 18639.3133597285 3536.9343891403 0.0))
((0 . "LINE") (100 . "AcDbEntity") (8 . "ARCH") (62 . 7) (370 . 13) (100 . "AcDbLine") (10 17748.7887104072
3476.5610859729 0.0) (11 18644.71739819 3476.5610859729 0.0))
((0 . "LINE") (100 . "AcDbEntity") (8 . "ARCH") (62 . 7) (370 . 13) (100 . "AcDbLine") (10 17745.7511199095
3438.5067873303 0.0) (11 18654.9630656109 3438.5067873303 0.0))
((0 . "LINE") (100 . "AcDbEntity") (8 . "ARCH") (62 . 7) (370 . 13) (100 . "AcDbLine") (10 17743.0295701357
3404.4117647059 0.0) (11 18664.2882013575 3404.4117647059 0.0))
((0 . "LINE") (100 . "AcDbEntity") (8 . "ARCH") (62 . 7) (370 . 13) (100 . "AcDbLine") (10 17736.916459276
3371.3574660633 0.0) (11 18673.3286877828 3371.3574660633 0.0))
((0 . "LINE") (100 . "AcDbEntity") (8 . "ARCH") (62 . 7) (370 . 13) (100 . "AcDbLine") (10 17720.284739819
3303.1674208145 0.0) (11 18691.978959276 3303.1674208145 0.0))
((0 . "LINE") (100 . "AcDbEntity") (8 . "ARCH") (62 . 7) (370 . 13) (100 . "AcDbLine") (10 18887.206561086
3303.1674208145 0.0) (11 18924.6095475113 3303.1674208145 0.0))
((0 . "LINE") (100 . "AcDbEntity") (8 . "ARCH") (62 . 7) (370 . 13) (100 . "AcDbLine") (10 19038.4615384615
916.2895927602 0.0) (11 19038.4615384615 520.3619909502 0.0))
((0 . "LINE") (100 . "AcDbEntity") (8 . "ARCH") (62 . 7) (370 . 13) (100 . "AcDbLine") (10 19038.4615384615
520.3619909502 0.0) (11 19038.4615384615 497.7375565611 0.0))
((0 . "LINE") (100 . "AcDbEntity") (8 . "ARCH") (62 . 7) (370 . 13) (100 . "AcDbLine") (10 19038.4615384615
497.7375565611 0.0) (11 18893.3944343891 497.7375565611 0.0))
((0 . "LINE") (100 . "AcDbEntity") (8 . "ARCH") (62 . 7) (370 . 13) (100 . "AcDbLine") (10 18685.7910859729
497.7375565611 0.0) (11 17725.8028959276 497.7375565611 0.0))
((0 . "LINE") (100 . "AcDbEntity") (8 . "ARCH") (62 . 7) (370 . 13) (100 . "AcDbLine") (10 18993.2126696833
916.2895927602 0.0) (11 18993.2126696833 890.3280542986 0.0))
((0 . "LINE") (100 . "AcDbEntity") (8 . "ARCH") (62 . 7) (370 . 13) (100 . "AcDbLine") (10 18993.2126696833
890.3280542986 0.0) (11 18993.2126696833 851.628959276 0.0))
((0 . "LINE") (100 . "AcDbEntity") (8 . "ARCH") (62 . 7) (370 . 13) (100 . "AcDbLine") (10 18993.2126696833
851.628959276 0.0) (11 18993.2126696833 812.036199095 0.0))
((0 . "LINE") (100 . "AcDbEntity") (8 . "ARCH") (62 . 7) (370 . 13) (100 . "AcDbLine") (10 18993.2126696833
812.036199095 0.0) (11 18993.2126696833 756.3914027149 0.0))
((0 . "LINE") (100 . "AcDbEntity") (8 . "ARCH") (62 . 7) (370 . 13) (100 . "AcDbLine") (10 18993.2126696833
756.3914027149 0.0) (11 18993.2126696833 691.8438914027 0.0))
((0 . "LINE") (100 . "AcDbEntity") (8 . "ARCH") (62 . 7) (370 . 13) (100 . "AcDbLine") (10 18993.2126696833
691.8438914027 0.0) (11 18993.2126696833 634.3325791855 0.0))
((0 . "LINE") (100 . "AcDbEntity") (8 . "ARCH") (62 . 7) (370 . 13) (100 . "AcDbLine") (10 18993.2126696833
634.3325791855 0.0) (11 18993.2126696833 571.1312217195 0.0))
((0 . "LINE") (100 . "AcDbEntity") (8 . "ARCH") (62 . 7) (370 . 13) (100 . "AcDbLine") (10 18993.2126696833
571.1312217195 0.0) (11 18993.2126696833 520.3619909502 0.0))
((0 . "LINE") (100 . "AcDbEntity") (8 . "ARCH") (62 . 7) (370 . 13) (100 . "AcDbLine") (10 17768.0915158371
890.3280542986 0.0) (11 18623.0718552036 890.3280542986 0.0))
((0 . "LINE") (100 . "AcDbEntity") (8 . "ARCH") (62 . 7) (370 . 13) (100 . "AcDbLine") (10 18956.1136651584
890.3280542986 0.0) (11 18993.2126696833 890.3280542986 0.0))
((0 . "LINE") (100 . "AcDbEntity") (8 . "ARCH") (62 . 7) (370 . 13) (100 . "AcDbLine") (10 17765.0024547511
851.628959276 0.0) (11 18626.5358371041 851.628959276 0.0))
((0 . "LINE") (100 . "AcDbEntity") (8 . "ARCH") (62 . 7) (370 . 13) (100 . "AcDbLine") (10 18952.6496832579
851.628959276 0.0) (11 18993.2126696833 851.628959276 0.0))
((0 . "LINE") (100 . "AcDbEntity") (8 . "ARCH") (62 . 7) (370 . 13) (100 . "AcDbLine") (10 17761.8420588235
812.036199095 0.0) (11 18630.0798076923 812.036199095 0.0))
((0 . "LINE") (100 . "AcDbEntity") (8 . "ARCH") (62 . 7) (370 . 13) (100 . "AcDbLine") (10 18949.1057126697
812.036199095 0.0) (11 18993.2126696833 812.036199095 0.0))
((0 . "LINE") (100 . "AcDbEntity") (8 . "ARCH") (62 . 7) (370 . 13) (100 . "AcDbLine") (10 17757.4003506787
756.3914027149 0.0) (11 18635.0605995475 756.3914027149 0.0))
((0 . "LINE") (100 . "AcDbEntity") (8 . "ARCH") (62 . 7) (370 . 13) (100 . "AcDbLine") (10 18944.1249208145
756.3914027149 0.0) (11 18993.2126696833 756.3914027149 0.0))
((0 . "LINE") (100 . "AcDbEntity") (8 . "ARCH") (62 . 7) (370 . 13) (100 . "AcDbLine") (10 17752.2479977376
691.8438914027 0.0) (11 18640.8382692308 691.8438914027 0.0))
((0 . "LINE") (100 . "AcDbEntity") (8 . "ARCH") (62 . 7) (370 . 13) (100 . "AcDbLine") (10 18938.3472511312
691.8438914027 0.0) (11 18993.2126696833 691.8438914027 0.0))
((0 . "LINE") (100 . "AcDbEntity") (8 . "ARCH") (62 . 7) (370 . 13) (100 . "AcDbLine") (10 17747.6572963801
634.3325791855 0.0) (11 18648.4317647059 634.3325791855 0.0))
((0 . "LINE") (100 . "AcDbEntity") (8 . "ARCH") (62 . 7) (370 . 13) (100 . "AcDbLine") (10 18930.7537556561
634.3325791855 0.0) (11 18993.2126696833 634.3325791855 0.0))
((0 . "LINE") (100 . "AcDbEntity") (8 . "ARCH") (62 . 7) (370 . 13) (100 . "AcDbLine") (10 17742.61239819 571.1312217195
0.0) (11 18665.71760181 571.1312217195 0.0))
((0 . "LINE") (100 . "AcDbEntity") (8 . "ARCH") (62 . 7) (370 . 13) (100 . "AcDbLine") (10 18913.467918552
571.1312217195 0.0) (11 18993.2126696833 571.1312217195 0.0))
((0 . "LINE") (100 . "AcDbEntity") (8 . "ARCH") (62 . 7) (370 . 13) (100 . "AcDbLine") (10 17731.321040724
520.3619909502 0.0) (11 18679.6032013575 520.3619909502 0.0))
((0 . "LINE") (100 . "AcDbEntity") (8 . "ARCH") (62 . 7) (370 . 13) (100 . "AcDbLine") (10 18899.5823190045
520.3619909502 0.0) (11 18993.2126696833 520.3619909502 0.0))
((0 . "LINE") (100 . "AcDbEntity") (8 . "ARCH") (62 . 7) (370 . 13) (100 . "AcDbLine") (10 18993.2126696833
520.3619909502 0.0) (11 19038.4615384615 520.3619909502 0.0))
((0 . "LINE") (100 . "AcDbEntity") (8 . "ARCH") (62 . 7) (370 . 13) (100 . "AcDbLine") (10 19038.4615384615
520.3619909502 0.0) (11 19061.0859728507 520.3619909502 0.0))
((0 . "LINE") (100 . "AcDbEntity") (8 . "ARCH") (62 . 7) (370 . 13) (100 . "AcDbLine") (10 8201.3574660633
3269.2307692308 0.0) (11 9309.9547511312 3269.2307692308 0.0))
((0 . "LINE") (100 . "AcDbEntity") (8 . "ARCH") (62 . 7) (370 . 13) (100 . "AcDbLine") (10 9309.9547511312
3269.2307692308 0.0) (11 9309.9547511312 3190.0452488688 0.0))
((0 . "LINE") (100 . "AcDbEntity") (8 . "ARCH") (62 . 7) (370 . 13) (100 . "AcDbLine") (10 9309.9547511312
3190.0452488688 0.0) (11 9287.3303167421 3190.0452488688 0.0))
((0 . "LINE") (100 . "AcDbEntity") (8 . "ARCH") (62 . 7) (370 . 13) (100 . "AcDbLine") (10 9287.3303167421
3190.0452488688 0.0) (11 8223.9819004525 3190.0452488688 0.0))
((0 . "LINE") (100 . "AcDbEntity") (8 . "ARCH") (62 . 7) (370 . 13) (100 . "AcDbLine") (10 8223.9819004525
3190.0452488688 0.0) (11 8201.3574660633 3190.0452488688 0.0))
((0 . "LINE") (100 . "AcDbEntity") (8 . "ARCH") (62 . 7) (370 . 13) (100 . "AcDbLine") (10 8201.3574660633
3190.0452488688 0.0) (11 8201.3574660633 3269.2307692308 0.0))
((0 . "LINE") (100 . "AcDbEntity") (8 . "ARCH") (62 . 7) (370 . 13) (100 . "AcDbLine") (10 8223.9819004525
3190.0452488688 0.0) (11 8291.8552036199 3122.1719457014 0.0))
((0 . "LINE") (100 . "AcDbEntity") (8 . "ARCH") (62 . 7) (370 . 13) (100 . "AcDbLine") (10 8291.8552036199
3122.1719457014 0.0) (11 8303.1674208145 3110.8597285068 0.0))
((0 . "LINE") (100 . "AcDbEntity") (8 . "ARCH") (62 . 7) (370 . 13) (100 . "AcDbLine") (10 8303.1674208145
3110.8597285068 0.0) (11 8314.4796380091 3076.9230769231 0.0))
((0 . "LINE") (100 . "AcDbEntity") (8 . "ARCH") (62 . 7) (370 . 13) (100 . "AcDbLine") (10 8314.4796380091
3076.9230769231 0.0) (11 9208.1447963801 3076.9230769231 0.0))
((0 . "LINE") (100 . "AcDbEntity") (8 . "ARCH") (62 . 7) (370 . 13) (100 . "AcDbLine") (10 9208.1447963801
3076.9230769231 0.0) (11 9219.4570135747 3110.8597285068 0.0))
((0 . "LINE") (100 . "AcDbEntity") (8 . "ARCH") (62 . 7) (370 . 13) (100 . "AcDbLine") (10 9219.4570135747
3110.8597285068 0.0) (11 9229.1532013575 3122.1719457014 0.0))
((0 . "LINE") (100 . "AcDbEntity") (8 . "ARCH") (62 . 7) (370 . 13) (100 . "AcDbLine") (10 9229.1532013575
3122.1719457014 0.0) (11 9287.3303167421 3190.0452488688 0.0))
((0 . "LINE") (100 . "AcDbEntity") (8 . "ARCH") (62 . 7) (370 . 13) (100 . "AcDbLine") (10 8291.8552036199
3122.1719457014 0.0) (11 9229.1532013575 3122.1719457014 0.0))
((0 . "LINE") (100 . "AcDbEntity") (8 . "ARCH") (62 . 7) (370 . 13) (100 . "AcDbLine") (10 9229.1532013575
3122.1719457014 0.0) (11 9230.7692307692 3122.1719457014 0.0))
((0 . "LINE") (100 . "AcDbEntity") (8 . "ARCH") (62 . 7) (370 . 13) (100 . "AcDbLine") (10 7929.8642533937 158.371040724
0.0) (11 9547.5113122172 158.371040724 0.0))
((0 . "LINE") (100 . "AcDbEntity") (8 . "ARCH") (62 . 7) (370 . 13) (100 . "AcDbLine") (10 7929.8642533937
101.8099547511 0.0) (11 9547.5113122172 101.8099547511 0.0))
((0 . "LINE") (100 . "AcDbEntity") (8 . "ARCH") (62 . 7) (370 . 13) (100 . "AcDbLine") (10 7929.8642533937 45.2488687783
0.0) (11 9547.5113122172 45.2488687783 0.0))
((0 . "LINE") (100 . "AcDbEntity") (8 . "ARCH") (62 . 7) (370 . 13) (100 . "AcDbLine") (10 10701.3574660633
3269.2307692308 0.0) (11 11809.9547511312 3269.2307692308 0.0))
((0 . "LINE") (100 . "AcDbEntity") (8 . "ARCH") (62 . 7) (370 . 13) (100 . "AcDbLine") (10 11809.9547511312
3269.2307692308 0.0) (11 11809.9547511312 3190.0452488688 0.0))
((0 . "LINE") (100 . "AcDbEntity") (8 . "ARCH") (62 . 7) (370 . 13) (100 . "AcDbLine") (10 11809.9547511312
3190.0452488688 0.0) (11 11787.3303167421 3190.0452488688 0.0))
((0 . "LINE") (100 . "AcDbEntity") (8 . "ARCH") (62 . 7) (370 . 13) (100 . "AcDbLine") (10 11787.3303167421
3190.0452488688 0.0) (11 10723.9819004525 3190.0452488688 0.0))
((0 . "LINE") (100 . "AcDbEntity") (8 . "ARCH") (62 . 7) (370 . 13) (100 . "AcDbLine") (10 10723.9819004525
3190.0452488688 0.0) (11 10701.3574660633 3190.0452488688 0.0))
((0 . "LINE") (100 . "AcDbEntity") (8 . "ARCH") (62 . 7) (370 . 13) (100 . "AcDbLine") (10 10701.3574660633
3190.0452488688 0.0) (11 10701.3574660633 3269.2307692308 0.0))
((0 . "LINE") (100 . "AcDbEntity") (8 . "ARCH") (62 . 7) (370 . 13) (100 . "AcDbLine") (10 10723.9819004525
3190.0452488688 0.0) (11 10791.8552036199 3122.1719457014 0.0))
((0 . "LINE") (100 . "AcDbEntity") (8 . "ARCH") (62 . 7) (370 . 13) (100 . "AcDbLine") (10 10791.8552036199
3122.1719457014 0.0) (11 10803.1674208145 3110.8597285068 0.0))
((0 . "LINE") (100 . "AcDbEntity") (8 . "ARCH") (62 . 7) (370 . 13) (100 . "AcDbLine") (10 10803.1674208145
3110.8597285068 0.0) (11 10814.4796380091 3076.9230769231 0.0))
((0 . "LINE") (100 . "AcDbEntity") (8 . "ARCH") (62 . 7) (370 . 13) (100 . "AcDbLine") (10 10814.4796380091
3076.9230769231 0.0) (11 11708.1447963801 3076.9230769231 0.0))
((0 . "LINE") (100 . "AcDbEntity") (8 . "ARCH") (62 . 7) (370 . 13) (100 . "AcDbLine") (10 11708.1447963801
3076.9230769231 0.0) (11 11719.4570135747 3110.8597285068 0.0))
((0 . "LINE") (100 . "AcDbEntity") (8 . "ARCH") (62 . 7) (370 . 13) (100 . "AcDbLine") (10 11719.4570135747
3110.8597285068 0.0) (11 11729.1532013575 3122.1719457014 0.0))
((0 . "LINE") (100 . "AcDbEntity") (8 . "ARCH") (62 . 7) (370 . 13) (100 . "AcDbLine") (10 11729.1532013575
3122.1719457014 0.0) (11 11787.3303167421 3190.0452488688 0.0))
((0 . "LINE") (100 . "AcDbEntity") (8 . "ARCH") (62 . 7) (370 . 13) (100 . "AcDbLine") (10 10791.8552036199
3122.1719457014 0.0) (11 11729.1532013575 3122.1719457014 0.0))
((0 . "LINE") (100 . "AcDbEntity") (8 . "ARCH") (62 . 7) (370 . 13) (100 . "AcDbLine") (10 11729.1532013575
3122.1719457014 0.0) (11 11730.7692307692 3122.1719457014 0.0))
((0 . "LINE") (100 . "AcDbEntity") (8 . "ARCH") (62 . 7) (370 . 13) (100 . "AcDbLine") (10 10452.4886877828
158.371040724 0.0) (11 12036.1990950226 158.371040724 0.0))
((0 . "LINE") (100 . "AcDbEntity") (8 . "ARCH") (62 . 7) (370 . 13) (100 . "AcDbLine") (10 10452.4886877828
101.8099547511 0.0) (11 12036.1990950226 101.8099547511 0.0))
((0 . "LINE") (100 . "AcDbEntity") (8 . "ARCH") (62 . 7) (370 . 13) (100 . "AcDbLine") (10 10452.4886877828
45.2488687783 0.0) (11 12036.1990950226 45.2488687783 0.0))
((0 . "LINE") (100 . "AcDbEntity") (8 . "ARCH") (62 . 7) (370 . 13) (100 . "AcDbLine") (10 2703.6199095023
6730.7692307692 0.0) (11 2726.2443438914 6696.8325791855 0.0))
((0 . "LINE") (100 . "AcDbEntity") (8 . "ARCH") (62 . 7) (370 . 13) (100 . "AcDbLine") (10 2726.2443438914
6696.8325791855 0.0) (11 2726.2443438914 6549.7737556561 0.0))
((0 . "LINE") (100 . "AcDbEntity") (8 . "ARCH") (62 . 7) (370 . 13) (100 . "AcDbLine") (10 2726.2443438914
6549.7737556561 0.0) (11 2726.2443438914 6481.9004524887 0.0))
((0 . "LINE") (100 . "AcDbEntity") (8 . "ARCH") (62 . 7) (370 . 13) (100 . "AcDbLine") (10 4276.0180995475
6481.9004524887 0.0) (11 4309.9547511312 6481.9004524887 0.0))
((0 . "LINE") (100 . "AcDbEntity") (8 . "ARCH") (62 . 7) (370 . 13) (100 . "AcDbLine") (10 4309.9547511312
6481.9004524887 0.0) (11 4309.9547511312 6549.7737556561 0.0))
((0 . "LINE") (100 . "AcDbEntity") (8 . "ARCH") (62 . 7) (370 . 13) (100 . "AcDbLine") (10 4309.9547511312
6549.7737556561 0.0) (11 4309.9547511312 6696.8325791855 0.0))
((0 . "LINE") (100 . "AcDbEntity") (8 . "ARCH") (62 . 7) (370 . 13) (100 . "AcDbLine") (10 4309.9547511312
6696.8325791855 0.0) (11 4338.2352941176 6730.7692307692 0.0))
((0 . "LINE") (100 . "AcDbEntity") (8 . "ARCH") (62 . 7) (370 . 13) (100 . "AcDbLine") (10 6549.7737556561
6730.7692307692 0.0) (11 6572.3981900452 6696.8325791855 0.0))
((0 . "LINE") (100 . "AcDbEntity") (8 . "ARCH") (62 . 7) (370 . 13) (100 . "AcDbLine") (10 6572.3981900452
6696.8325791855 0.0) (11 6572.3981900452 6549.7737556561 0.0))
((0 . "LINE") (100 . "AcDbEntity") (8 . "ARCH") (62 . 7) (370 . 13) (100 . "AcDbLine") (10 6572.3981900452
6549.7737556561 0.0) (11 6572.3981900452 6481.9004524887 0.0))
((0 . "LINE") (100 . "AcDbEntity") (8 . "ARCH") (62 . 7) (370 . 13) (100 . "AcDbLine") (10 6572.3981900452
6481.9004524887 0.0) (11 6628.9592760181 6481.9004524887 0.0))
((0 . "LINE") (100 . "AcDbEntity") (8 . "ARCH") (62 . 7) (370 . 13) (100 . "AcDbLine") (10 7941.1764705882
6481.9004524887 0.0) (11 8009.0497737557 6481.9004524887 0.0))
((0 . "LINE") (100 . "AcDbEntity") (8 . "ARCH") (62 . 7) (370 . 13) (100 . "AcDbLine") (10 8009.0497737557
6481.9004524887 0.0) (11 8009.0497737557 6549.7737556561 0.0))
((0 . "LINE") (100 . "AcDbEntity") (8 . "ARCH") (62 . 7) (370 . 13) (100 . "AcDbLine") (10 8009.0497737557
6549.7737556561 0.0) (11 8009.0497737557 6696.8325791855 0.0))
((0 . "LINE") (100 . "AcDbEntity") (8 . "ARCH") (62 . 7) (370 . 13) (100 . "AcDbLine") (10 8009.0497737557
6696.8325791855 0.0) (11 8037.3303167421 6730.7692307692 0.0))
((0 . "LINE") (100 . "AcDbEntity") (8 . "ARCH") (62 . 7) (370 . 13) (100 . "AcDbLine") (10 11957.0135746606
6730.7692307692 0.0) (11 11979.6380090498 6696.8325791855 0.0))
((0 . "LINE") (100 . "AcDbEntity") (8 . "ARCH") (62 . 7) (370 . 13) (100 . "AcDbLine") (10 11979.6380090498
6696.8325791855 0.0) (11 11979.6380090498 6549.7737556561 0.0))
((0 . "LINE") (100 . "AcDbEntity") (8 . "ARCH") (62 . 7) (370 . 13) (100 . "AcDbLine") (10 11979.6380090498
6549.7737556561 0.0) (11 11979.6380090498 6481.9004524887 0.0))
((0 . "LINE") (100 . "AcDbEntity") (8 . "ARCH") (62 . 7) (370 . 13) (100 . "AcDbLine") (10 11979.6380090498
6481.9004524887 0.0) (11 12036.1990950226 6481.9004524887 0.0))
((0 . "LINE") (100 . "AcDbEntity") (8 . "ARCH") (62 . 7) (370 . 13) (100 . "AcDbLine") (10 13348.4162895928
6481.9004524887 0.0) (11 13438.9140271493 6481.9004524887 0.0))
((0 . "LINE") (100 . "AcDbEntity") (8 . "ARCH") (62 . 7) (370 . 13) (100 . "AcDbLine") (10 13438.9140271493
6481.9004524887 0.0) (11 13438.9140271493 6549.7737556561 0.0))
((0 . "LINE") (100 . "AcDbEntity") (8 . "ARCH") (62 . 7) (370 . 13) (100 . "AcDbLine") (10 13438.9140271493
6549.7737556561 0.0) (11 13438.9140271493 6696.8325791855 0.0))
((0 . "LINE") (100 . "AcDbEntity") (8 . "ARCH") (62 . 7) (370 . 13) (100 . "AcDbLine") (10 13438.9140271493
6696.8325791855 0.0) (11 13467.1945701357 6730.7692307692 0.0))
((0 . "LINE") (100 . "AcDbEntity") (8 . "ARCH") (62 . 7) (370 . 13) (100 . "AcDbLine") (10 15690.0452488688
6730.7692307692 0.0) (11 15712.6696832579 6696.8325791855 0.0))
((0 . "LINE") (100 . "AcDbEntity") (8 . "ARCH") (62 . 7) (370 . 13) (100 . "AcDbLine") (10 15712.6696832579
6696.8325791855 0.0) (11 15712.6696832579 6549.7737556561 0.0))
((0 . "LINE") (100 . "AcDbEntity") (8 . "ARCH") (62 . 7) (370 . 13) (100 . "AcDbLine") (10 15712.6696832579
6549.7737556561 0.0) (11 15712.6696832579 6481.9004524887 0.0))
((0 . "LINE") (100 . "AcDbEntity") (8 . "ARCH") (62 . 7) (370 . 13) (100 . "AcDbLine") (10 15712.6696832579
6481.9004524887 0.0) (11 15769.2307692308 6481.9004524887 0.0))
((0 . "LINE") (100 . "AcDbEntity") (8 . "ARCH") (62 . 7) (370 . 13) (100 . "AcDbLine") (10 17330.3167420814
6481.9004524887 0.0) (11 17330.3167420814 6549.7737556561 0.0))
((0 . "LINE") (100 . "AcDbEntity") (8 . "ARCH") (62 . 7) (370 . 13) (100 . "AcDbLine") (10 17330.3167420814
6549.7737556561 0.0) (11 17330.3167420814 6696.8325791855 0.0))
((0 . "LINE") (100 . "AcDbEntity") (8 . "ARCH") (62 . 7) (370 . 13) (100 . "AcDbLine") (10 17330.3167420814
6696.8325791855 0.0) (11 17358.5972850679 6730.7692307692 0.0))
((0 . "LINE") (100 . "AcDbEntity") (8 . "LOUVERS") (62 . 7) (370 . 13) (100 . "AcDbLine") (10 9106.334841629
6762.4547511312 0.0) (11 9377.8280542986 6762.4547511312 0.0))
((0 . "LINE") (100 . "AcDbEntity") (8 . "LOUVERS") (62 . 7) (370 . 13) (100 . "AcDbLine") (10 9106.334841629
6710.6787330317 0.0) (11 9402.9411764706 6710.6787330317 0.0))
((0 . "LINE") (100 . "AcDbEntity") (8 . "LOUVERS") (62 . 7) (370 . 13) (100 . "AcDbLine") (10 9106.334841629
6643.0995475113 0.0) (11 9468.3257918552 6643.0995475113 0.0))
((0 . "LINE") (100 . "AcDbEntity") (8 . "LOUVERS") (62 . 7) (370 . 13) (100 . "AcDbLine") (10 9106.334841629
6607.2624434389 0.0) (11 9479.6380090498 6607.2624434389 0.0))
((0 . "LINE") (100 . "AcDbEntity") (8 . "LOUVERS") (62 . 7) (370 . 13) (100 . "AcDbLine") (10 10633.4841628959
6761.8212669683 0.0) (11 10927.6018099548 6761.8212669683 0.0))
((0 . "LINE") (100 . "AcDbEntity") (8 . "LOUVERS") (62 . 7) (370 . 13) (100 . "AcDbLine") (10 10617.2087104072
6717.7488687783 0.0) (11 10927.6018099548 6717.7488687783 0.0))
((0 . "LINE") (100 . "AcDbEntity") (8 . "LOUVERS") (62 . 7) (370 . 13) (100 . "AcDbLine") (10 10579.9632352941
6687.9524886878 0.0) (11 10927.6018099548 6687.9524886878 0.0))
((0 . "LINE") (100 . "AcDbEntity") (8 . "LOUVERS") (62 . 7) (370 . 13) (100 . "AcDbLine") (10 10541.556561086
6641.3122171946 0.0) (11 10927.6018099548 6641.3122171946 0.0))
((0 . "LINE") (100 . "AcDbEntity") (8 . "LOUVERS") (62 . 7) (370 . 13) (100 . "AcDbLine") (10 10531.6742081448
6607.0701357466 0.0) (11 10927.6018099548 6607.0701357466 0.0))
((0 . "LINE") (100 . "AcDbEntity") (8 . "LOUVERS") (62 . 7) (370 . 13) (100 . "AcDbLine") (10 4140.2714932127
5531.6742081448 0.0) (11 4172.0475113122 5531.6742081448 0.0))
((0 . "LINE") (100 . "AcDbEntity") (8 . "LOUVERS") (62 . 7) (370 . 13) (100 . "AcDbLine") (10 4172.0475113122
5531.6742081448 0.0) (11 4174.2081447964 5531.6742081448 0.0))
((0 . "LINE") (100 . "AcDbEntity") (8 . "LOUVERS") (62 . 7) (370 . 13) (100 . "AcDbLine") (10 4671.9457013575
5531.6742081448 0.0) (11 4671.9457013575 5045.2488687783 0.0))
((0 . "LINE") (100 . "AcDbEntity") (8 . "LOUVERS") (62 . 7) (370 . 13) (100 . "AcDbLine") (10 4671.9457013575
5045.2488687783 0.0) (11 4671.9457013575 4050.1064705882 0.0))
((0 . "LINE") (100 . "AcDbEntity") (8 . "LOUVERS") (62 . 7) (370 . 13) (100 . "AcDbLine") (10 4140.2714932127
4091.2518891403 0.0) (11 4140.2714932127 4208.1447963801 0.0))
((0 . "LINE") (100 . "AcDbEntity") (8 . "LOUVERS") (62 . 7) (370 . 13) (100 . "AcDbLine") (10 4140.2714932127
4314.4796380091 0.0) (11 4140.2714932127 5531.6742081448 0.0))
((0 . "LINE") (100 . "AcDbEntity") (8 . "LOUVERS") (62 . 7) (370 . 13) (100 . "AcDbLine") (10 4172.0475113122
5531.6742081448 0.0) (11 4172.0475113122 4295.4140271493 0.0))
((0 . "LINE") (100 . "AcDbEntity") (8 . "LOUVERS") (62 . 7) (370 . 13) (100 . "AcDbLine") (10 4233.0656108597
5531.6742081448 0.0) (11 4233.0656108597 4258.8031674208 0.0))
((0 . "LINE") (100 . "AcDbEntity") (8 . "LOUVERS") (62 . 7) (370 . 13) (100 . "AcDbLine") (10 4252.1719457014
5531.6742081448 0.0) (11 4252.1719457014 4247.3393665158 0.0))
((0 . "LINE") (100 . "AcDbEntity") (8 . "LOUVERS") (62 . 7) (370 . 13) (100 . "AcDbLine") (10 4310.9502262443
5531.6742081448 0.0) (11 4310.9502262443 4212.07239819 0.0))
((0 . "LINE") (100 . "AcDbEntity") (8 . "LOUVERS") (62 . 7) (370 . 13) (100 . "AcDbLine") (10 4331.0859728507
5531.6742081448 0.0) (11 4331.0859728507 4199.9909502262 0.0))
((0 . "LINE") (100 . "AcDbEntity") (8 . "LOUVERS") (62 . 7) (370 . 13) (100 . "AcDbLine") (10 4392.8959276018
5531.6742081448 0.0) (11 4392.8959276018 4240.3455316742 0.0))
((0 . "LINE") (100 . "AcDbEntity") (8 . "LOUVERS") (62 . 7) (370 . 13) (100 . "AcDbLine") (10 4460.6221719457
5531.6742081448 0.0) (11 4460.6221719457 4338.8564366516 0.0))
((0 . "LINE") (100 . "AcDbEntity") (8 . "LOUVERS") (62 . 7) (370 . 13) (100 . "AcDbLine") (10 4499.0384615385
5531.6742081448 0.0) (11 4499.0384615385 4319.6314140271 0.0))
((0 . "LINE") (100 . "AcDbEntity") (8 . "LOUVERS") (62 . 7) (370 . 13) (100 . "AcDbLine") (10 4578.9592760181
5531.6742081448 0.0) (11 4578.9592760181 4126.4894457014 0.0))
((0 . "LINE") (100 . "AcDbEntity") (8 . "LOUVERS") (62 . 7) (370 . 13) (100 . "AcDbLine") (10 4640.7918552036
5531.6742081448 0.0) (11 4640.7918552036 4043.6924434389 0.0))
((0 . "LINE") (100 . "AcDbEntity") (8 . "LOUVERS") (62 . 7) (370 . 13) (100 . "AcDbLine") (10 6674.2081447964
5531.6742081448 0.0) (11 6708.1447963801 5531.6742081448 0.0))
((0 . "LINE") (100 . "AcDbEntity") (8 . "LOUVERS") (62 . 7) (370 . 13) (100 . "AcDbLine") (10 6708.1447963801
5531.6742081448 0.0) (11 6708.1447963801 4276.0180995475 0.0))
((0 . "LINE") (100 . "AcDbEntity") (8 . "LOUVERS") (62 . 7) (370 . 13) (100 . "AcDbLine") (10 6210.407239819
4231.9599886878 0.0) (11 6210.407239819 5045.2488687783 0.0))
((0 . "LINE") (100 . "AcDbEntity") (8 . "LOUVERS") (62 . 7) (370 . 13) (100 . "AcDbLine") (10 6210.407239819
5045.2488687783 0.0) (11 6210.407239819 5531.6742081448 0.0))
((0 . "LINE") (100 . "AcDbEntity") (8 . "LOUVERS") (62 . 7) (370 . 13) (100 . "AcDbLine") (10 6234.2647058824
5531.6742081448 0.0) (11 6234.2647058824 4252.0504864253 0.0))
((0 . "LINE") (100 . "AcDbEntity") (8 . "LOUVERS") (62 . 7) (370 . 13) (100 . "AcDbLine") (10 6294.2194570136
5531.6742081448 0.0) (11 6294.2194570136 4300.6254072398 0.0))
((0 . "LINE") (100 . "AcDbEntity") (8 . "LOUVERS") (62 . 7) (370 . 13) (100 . "AcDbLine") (10 6374.4230769231
5531.6742081448 0.0) (11 6374.4230769231 4334.9983823529 0.0))
((0 . "LINE") (100 . "AcDbEntity") (8 . "LOUVERS") (62 . 7) (370 . 13) (100 . "AcDbLine") (10 6454.7737556561
5531.6742081448 0.0) (11 6454.7737556561 4349.4909502262 0.0))
((0 . "LINE") (100 . "AcDbEntity") (8 . "LOUVERS") (62 . 7) (370 . 13) (100 . "AcDbLine") (10 6508.2918552036
5531.6742081448 0.0) (11 6508.2918552036 4215.6957013575 0.0))
((0 . "LINE") (100 . "AcDbEntity") (8 . "LOUVERS") (62 . 7) (370 . 13) (100 . "AcDbLine") (10 6523.9932126697
5531.6742081448 0.0) (11 6523.9932126697 4176.4423076923 0.0))
((0 . "LINE") (100 . "AcDbEntity") (8 . "LOUVERS") (62 . 7) (370 . 13) (100 . "AcDbLine") (10 6582.5113122172
5531.6742081448 0.0) (11 6582.5113122172 4175.5113122172 0.0))
((0 . "LINE") (100 . "AcDbEntity") (8 . "LOUVERS") (62 . 7) (370 . 13) (100 . "AcDbLine") (10 6658.6312217195
5531.6742081448 0.0) (11 6658.6312217195 4236.407239819 0.0))
((0 . "LINE") (100 . "AcDbEntity") (8 . "LOUVERS") (62 . 7) (370 . 13) (100 . "AcDbLine") (10 3235.2941176471
5712.6696832579 0.0) (11 3285.8031674208 5712.6696832579 0.0))
((0 . "LINE") (100 . "AcDbEntity") (8 . "LOUVERS") (62 . 7) (370 . 13) (100 . "AcDbLine") (10 3285.8031674208
5712.6696832579 0.0) (11 3315.9615384615 5712.6696832579 0.0))
((0 . "LINE") (100 . "AcDbEntity") (8 . "LOUVERS") (62 . 7) (370 . 13) (100 . "AcDbLine") (10 3315.9615384615
5712.6696832579 0.0) (11 3362.0814479638 5712.6696832579 0.0))
((0 . "LINE") (100 . "AcDbEntity") (8 . "LOUVERS") (62 . 7) (370 . 13) (100 . "AcDbLine") (10 3362.0814479638
5712.6696832579 0.0) (11 3390.8823529412 5712.6696832579 0.0))
((0 . "LINE") (100 . "AcDbEntity") (8 . "LOUVERS") (62 . 7) (370 . 13) (100 . "AcDbLine") (10 3390.8823529412
5712.6696832579 0.0) (11 3440.7126696833 5712.6696832579 0.0))
((0 . "LINE") (100 . "AcDbEntity") (8 . "LOUVERS") (62 . 7) (370 . 13) (100 . "AcDbLine") (10 3440.7126696833
5712.6696832579 0.0) (11 3507.0701357466 5712.6696832579 0.0))
((0 . "LINE") (100 . "AcDbEntity") (8 . "LOUVERS") (62 . 7) (370 . 13) (100 . "AcDbLine") (10 3507.0701357466
5712.6696832579 0.0) (11 3526.1538461538 5712.6696832579 0.0))
((0 . "LINE") (100 . "AcDbEntity") (8 . "LOUVERS") (62 . 7) (370 . 13) (100 . "AcDbLine") (10 3526.1538461538
5712.6696832579 0.0) (11 3573.5520361991 5712.6696832579 0.0))
((0 . "LINE") (100 . "AcDbEntity") (8 . "LOUVERS") (62 . 7) (370 . 13) (100 . "AcDbLine") (10 3573.5520361991
5712.6696832579 0.0) (11 3643.2352941176 5712.6696832579 0.0))
((0 . "LINE") (100 . "AcDbEntity") (8 . "LOUVERS") (62 . 7) (370 . 13) (100 . "AcDbLine") (10 3643.2352941176
5712.6696832579 0.0) (11 3663.9819004525 5712.6696832579 0.0))
((0 . "LINE") (100 . "AcDbEntity") (8 . "LOUVERS") (62 . 7) (370 . 13) (100 . "AcDbLine") (10 3663.9819004525
5712.6696832579 0.0) (11 3712.1380090498 5712.6696832579 0.0))
((0 . "LINE") (100 . "AcDbEntity") (8 . "LOUVERS") (62 . 7) (370 . 13) (100 . "AcDbLine") (10 3712.1380090498
5712.6696832579 0.0) (11 3739.8076923077 5712.6696832579 0.0))
((0 . "LINE") (100 . "AcDbEntity") (8 . "LOUVERS") (62 . 7) (370 . 13) (100 . "AcDbLine") (10 3739.8076923077
5712.6696832579 0.0) (11 3791.4705882353 5712.6696832579 0.0))
((0 . "LINE") (100 . "AcDbEntity") (8 . "LOUVERS") (62 . 7) (370 . 13) (100 . "AcDbLine") (10 3791.4705882353
5712.6696832579 0.0) (11 3800.9049773756 5712.6696832579 0.0))
((0 . "LINE") (100 . "AcDbEntity") (8 . "LOUVERS") (62 . 7) (370 . 13) (100 . "AcDbLine") (10 3800.9049773756
5712.6696832579 0.0) (11 3800.9049773756 5610.8597285068 0.0))
((0 . "LINE") (100 . "AcDbEntity") (8 . "LOUVERS") (62 . 7) (370 . 13) (100 . "AcDbLine") (10 3800.9049773756
5610.8597285068 0.0) (11 3800.9049773756 3800.9049773756 0.0))
((0 . "LINE") (100 . "AcDbEntity") (8 . "LOUVERS") (62 . 7) (370 . 13) (100 . "AcDbLine") (10 3800.9049773756
3800.9049773756 0.0) (11 3791.4705882353 3800.9049773756 0.0))
((0 . "LINE") (100 . "AcDbEntity") (8 . "LOUVERS") (62 . 7) (370 . 13) (100 . "AcDbLine") (10 3791.4705882353
3800.9049773756 0.0) (11 3739.8076923077 3800.9049773756 0.0))
((0 . "LINE") (100 . "AcDbEntity") (8 . "LOUVERS") (62 . 7) (370 . 13) (100 . "AcDbLine") (10 3739.8076923077
3800.9049773756 0.0) (11 3712.1380090498 3800.9049773756 0.0))
((0 . "LINE") (100 . "AcDbEntity") (8 . "LOUVERS") (62 . 7) (370 . 13) (100 . "AcDbLine") (10 3712.1380090498
3800.9049773756 0.0) (11 3663.9819004525 3800.9049773756 0.0))
((0 . "LINE") (100 . "AcDbEntity") (8 . "LOUVERS") (62 . 7) (370 . 13) (100 . "AcDbLine") (10 3663.9819004525
3800.9049773756 0.0) (11 3643.2352941176 3800.9049773756 0.0))
((0 . "LINE") (100 . "AcDbEntity") (8 . "LOUVERS") (62 . 7) (370 . 13) (100 . "AcDbLine") (10 3643.2352941176
3800.9049773756 0.0) (11 3573.5520361991 3800.9049773756 0.0))
((0 . "LINE") (100 . "AcDbEntity") (8 . "LOUVERS") (62 . 7) (370 . 13) (100 . "AcDbLine") (10 3573.5520361991
3800.9049773756 0.0) (11 3526.1538461538 3800.9049773756 0.0))
((0 . "LINE") (100 . "AcDbEntity") (8 . "LOUVERS") (62 . 7) (370 . 13) (100 . "AcDbLine") (10 3526.1538461538
3800.9049773756 0.0) (11 3507.0701357466 3800.9049773756 0.0))
((0 . "LINE") (100 . "AcDbEntity") (8 . "LOUVERS") (62 . 7) (370 . 13) (100 . "AcDbLine") (10 3507.0701357466
3800.9049773756 0.0) (11 3440.7126696833 3800.9049773756 0.0))
((0 . "LINE") (100 . "AcDbEntity") (8 . "LOUVERS") (62 . 7) (370 . 13) (100 . "AcDbLine") (10 3440.7126696833
3800.9049773756 0.0) (11 3390.8823529412 3800.9049773756 0.0))
((0 . "LINE") (100 . "AcDbEntity") (8 . "LOUVERS") (62 . 7) (370 . 13) (100 . "AcDbLine") (10 3390.8823529412
3800.9049773756 0.0) (11 3362.0814479638 3800.9049773756 0.0))
((0 . "LINE") (100 . "AcDbEntity") (8 . "LOUVERS") (62 . 7) (370 . 13) (100 . "AcDbLine") (10 3362.0814479638
3800.9049773756 0.0) (11 3315.9615384615 3800.9049773756 0.0))
((0 . "LINE") (100 . "AcDbEntity") (8 . "LOUVERS") (62 . 7) (370 . 13) (100 . "AcDbLine") (10 3315.9615384615
3800.9049773756 0.0) (11 3285.8031674208 3800.9049773756 0.0))
((0 . "LINE") (100 . "AcDbEntity") (8 . "LOUVERS") (62 . 7) (370 . 13) (100 . "AcDbLine") (10 3285.8031674208
3800.9049773756 0.0) (11 3235.2941176471 3800.9049773756 0.0))
((0 . "LINE") (100 . "AcDbEntity") (8 . "LOUVERS") (62 . 7) (370 . 13) (100 . "AcDbLine") (10 3235.2941176471
3800.9049773756 0.0) (11 3235.2941176471 5610.8597285068 0.0))
((0 . "LINE") (100 . "AcDbEntity") (8 . "LOUVERS") (62 . 7) (370 . 13) (100 . "AcDbLine") (10 3235.2941176471
5610.8597285068 0.0) (11 3235.2941176471 5712.6696832579 0.0))
((0 . "LINE") (100 . "AcDbEntity") (8 . "LOUVERS") (62 . 7) (370 . 13) (100 . "AcDbLine") (10 3285.8031674208
5712.6696832579 0.0) (11 3285.8031674208 5610.8597285068 0.0))
((0 . "LINE") (100 . "AcDbEntity") (8 . "LOUVERS") (62 . 7) (370 . 13) (100 . "AcDbLine") (10 3285.8031674208
5610.8597285068 0.0) (11 3285.8031674208 3800.9049773756 0.0))
((0 . "LINE") (100 . "AcDbEntity") (8 . "LOUVERS") (62 . 7) (370 . 13) (100 . "AcDbLine") (10 3315.9615384615
5712.6696832579 0.0) (11 3315.9615384615 5610.8597285068 0.0))
((0 . "LINE") (100 . "AcDbEntity") (8 . "LOUVERS") (62 . 7) (370 . 13) (100 . "AcDbLine") (10 3315.9615384615
5610.8597285068 0.0) (11 3315.9615384615 3800.9049773756 0.0))
((0 . "LINE") (100 . "AcDbEntity") (8 . "LOUVERS") (62 . 7) (370 . 13) (100 . "AcDbLine") (10 3362.0814479638
5712.6696832579 0.0) (11 3362.0814479638 5610.8597285068 0.0))
((0 . "LINE") (100 . "AcDbEntity") (8 . "LOUVERS") (62 . 7) (370 . 13) (100 . "AcDbLine") (10 3362.0814479638
5610.8597285068 0.0) (11 3362.0814479638 3800.9049773756 0.0))
((0 . "LINE") (100 . "AcDbEntity") (8 . "LOUVERS") (62 . 7) (370 . 13) (100 . "AcDbLine") (10 3390.8823529412
5712.6696832579 0.0) (11 3390.8823529412 5610.8597285068 0.0))
((0 . "LINE") (100 . "AcDbEntity") (8 . "LOUVERS") (62 . 7) (370 . 13) (100 . "AcDbLine") (10 3390.8823529412
5610.8597285068 0.0) (11 3390.8823529412 3800.9049773756 0.0))
((0 . "LINE") (100 . "AcDbEntity") (8 . "LOUVERS") (62 . 7) (370 . 13) (100 . "AcDbLine") (10 3440.7126696833
5712.6696832579 0.0) (11 3440.7126696833 5610.8597285068 0.0))
((0 . "LINE") (100 . "AcDbEntity") (8 . "LOUVERS") (62 . 7) (370 . 13) (100 . "AcDbLine") (10 3440.7126696833
5610.8597285068 0.0) (11 3440.7126696833 3800.9049773756 0.0))
((0 . "LINE") (100 . "AcDbEntity") (8 . "LOUVERS") (62 . 7) (370 . 13) (100 . "AcDbLine") (10 3507.0701357466
5712.6696832579 0.0) (11 3507.0701357466 5610.8597285068 0.0))
((0 . "LINE") (100 . "AcDbEntity") (8 . "LOUVERS") (62 . 7) (370 . 13) (100 . "AcDbLine") (10 3507.0701357466
5610.8597285068 0.0) (11 3507.0701357466 3800.9049773756 0.0))
((0 . "LINE") (100 . "AcDbEntity") (8 . "LOUVERS") (62 . 7) (370 . 13) (100 . "AcDbLine") (10 3526.1538461538
5712.6696832579 0.0) (11 3526.1538461538 5610.8597285068 0.0))
((0 . "LINE") (100 . "AcDbEntity") (8 . "LOUVERS") (62 . 7) (370 . 13) (100 . "AcDbLine") (10 3526.1538461538
5610.8597285068 0.0) (11 3526.1538461538 3800.9049773756 0.0))
((0 . "LINE") (100 . "AcDbEntity") (8 . "LOUVERS") (62 . 7) (370 . 13) (100 . "AcDbLine") (10 3573.5520361991
5712.6696832579 0.0) (11 3573.5520361991 5610.8597285068 0.0))
((0 . "LINE") (100 . "AcDbEntity") (8 . "LOUVERS") (62 . 7) (370 . 13) (100 . "AcDbLine") (10 3573.5520361991
5610.8597285068 0.0) (11 3573.5520361991 3800.9049773756 0.0))
((0 . "LINE") (100 . "AcDbEntity") (8 . "LOUVERS") (62 . 7) (370 . 13) (100 . "AcDbLine") (10 3643.2352941176
5712.6696832579 0.0) (11 3643.2352941176 5610.8597285068 0.0))
((0 . "LINE") (100 . "AcDbEntity") (8 . "LOUVERS") (62 . 7) (370 . 13) (100 . "AcDbLine") (10 3643.2352941176
5610.8597285068 0.0) (11 3643.2352941176 3800.9049773756 0.0))
((0 . "LINE") (100 . "AcDbEntity") (8 . "LOUVERS") (62 . 7) (370 . 13) (100 . "AcDbLine") (10 3663.9819004525
5712.6696832579 0.0) (11 3663.9819004525 5610.8597285068 0.0))
((0 . "LINE") (100 . "AcDbEntity") (8 . "LOUVERS") (62 . 7) (370 . 13) (100 . "AcDbLine") (10 3663.9819004525
5610.8597285068 0.0) (11 3663.9819004525 3800.9049773756 0.0))
((0 . "LINE") (100 . "AcDbEntity") (8 . "LOUVERS") (62 . 7) (370 . 13) (100 . "AcDbLine") (10 3712.1380090498
5712.6696832579 0.0) (11 3712.1380090498 5610.8597285068 0.0))
((0 . "LINE") (100 . "AcDbEntity") (8 . "LOUVERS") (62 . 7) (370 . 13) (100 . "AcDbLine") (10 3712.1380090498
5610.8597285068 0.0) (11 3712.1380090498 3800.9049773756 0.0))
((0 . "LINE") (100 . "AcDbEntity") (8 . "LOUVERS") (62 . 7) (370 . 13) (100 . "AcDbLine") (10 3739.8076923077
5712.6696832579 0.0) (11 3739.8076923077 5610.8597285068 0.0))
((0 . "LINE") (100 . "AcDbEntity") (8 . "LOUVERS") (62 . 7) (370 . 13) (100 . "AcDbLine") (10 3739.8076923077
5610.8597285068 0.0) (11 3739.8076923077 3800.9049773756 0.0))
((0 . "LINE") (100 . "AcDbEntity") (8 . "LOUVERS") (62 . 7) (370 . 13) (100 . "AcDbLine") (10 3791.4705882353
5712.6696832579 0.0) (11 3791.4705882353 5610.8597285068 0.0))
((0 . "LINE") (100 . "AcDbEntity") (8 . "LOUVERS") (62 . 7) (370 . 13) (100 . "AcDbLine") (10 3791.4705882353
5610.8597285068 0.0) (11 3791.4705882353 3800.9049773756 0.0))
((0 . "LINE") (100 . "AcDbEntity") (8 . "LOUVERS") (62 . 7) (370 . 13) (100 . "AcDbLine") (10 7047.5113122172
5712.6696832579 0.0) (11 7096.7647058824 5712.6696832579 0.0))
((0 . "LINE") (100 . "AcDbEntity") (8 . "LOUVERS") (62 . 7) (370 . 13) (100 . "AcDbLine") (10 7096.7647058824
5712.6696832579 0.0) (11 7127.8959276018 5712.6696832579 0.0))
((0 . "LINE") (100 . "AcDbEntity") (8 . "LOUVERS") (62 . 7) (370 . 13) (100 . "AcDbLine") (10 7127.8959276018
5712.6696832579 0.0) (11 7172.2058823529 5712.6696832579 0.0))
((0 . "LINE") (100 . "AcDbEntity") (8 . "LOUVERS") (62 . 7) (370 . 13) (100 . "AcDbLine") (10 7172.2058823529
5712.6696832579 0.0) (11 7202.0701357466 5712.6696832579 0.0))
((0 . "LINE") (100 . "AcDbEntity") (8 . "LOUVERS") (62 . 7) (370 . 13) (100 . "AcDbLine") (10 7202.0701357466
5712.6696832579 0.0) (11 7246.0972850679 5712.6696832579 0.0))
((0 . "LINE") (100 . "AcDbEntity") (8 . "LOUVERS") (62 . 7) (370 . 13) (100 . "AcDbLine") (10 7246.0972850679
5712.6696832579 0.0) (11 7273.778280543 5712.6696832579 0.0))
((0 . "LINE") (100 . "AcDbEntity") (8 . "LOUVERS") (62 . 7) (370 . 13) (100 . "AcDbLine") (10 7273.778280543
5712.6696832579 0.0) (11 7322.4321266968 5712.6696832579 0.0))
((0 . "LINE") (100 . "AcDbEntity") (8 . "LOUVERS") (62 . 7) (370 . 13) (100 . "AcDbLine") (10 7322.4321266968
5712.6696832579 0.0) (11 7349.9321266968 5712.6696832579 0.0))
((0 . "LINE") (100 . "AcDbEntity") (8 . "LOUVERS") (62 . 7) (370 . 13) (100 . "AcDbLine") (10 7349.9321266968
5712.6696832579 0.0) (11 7393.7330316742 5712.6696832579 0.0))
((0 . "LINE") (100 . "AcDbEntity") (8 . "LOUVERS") (62 . 7) (370 . 13) (100 . "AcDbLine") (10 7393.7330316742
5712.6696832579 0.0) (11 7424.4909502262 5712.6696832579 0.0))
((0 . "LINE") (100 . "AcDbEntity") (8 . "LOUVERS") (62 . 7) (370 . 13) (100 . "AcDbLine") (10 7424.4909502262
5712.6696832579 0.0) (11 7463.6425339367 5712.6696832579 0.0))
((0 . "LINE") (100 . "AcDbEntity") (8 . "LOUVERS") (62 . 7) (370 . 13) (100 . "AcDbLine") (10 7463.6425339367
5712.6696832579 0.0) (11 7501.3800904977 5712.6696832579 0.0))
((0 . "LINE") (100 . "AcDbEntity") (8 . "LOUVERS") (62 . 7) (370 . 13) (100 . "AcDbLine") (10 7501.3800904977
5712.6696832579 0.0) (11 7529.7171945701 5712.6696832579 0.0))
((0 . "LINE") (100 . "AcDbEntity") (8 . "LOUVERS") (62 . 7) (370 . 13) (100 . "AcDbLine") (10 7529.7171945701
5712.6696832579 0.0) (11 7579.185520362 5712.6696832579 0.0))
((0 . "LINE") (100 . "AcDbEntity") (8 . "LOUVERS") (62 . 7) (370 . 13) (100 . "AcDbLine") (10 7579.185520362
5712.6696832579 0.0) (11 7579.185520362 5610.8597285068 0.0))
((0 . "LINE") (100 . "AcDbEntity") (8 . "LOUVERS") (62 . 7) (370 . 13) (100 . "AcDbLine") (10 7579.185520362
5610.8597285068 0.0) (11 7579.185520362 3800.9049773756 0.0))
((0 . "LINE") (100 . "AcDbEntity") (8 . "LOUVERS") (62 . 7) (370 . 13) (100 . "AcDbLine") (10 7579.185520362
3800.9049773756 0.0) (11 7529.7171945701 3800.9049773756 0.0))
((0 . "LINE") (100 . "AcDbEntity") (8 . "LOUVERS") (62 . 7) (370 . 13) (100 . "AcDbLine") (10 7529.7171945701
3800.9049773756 0.0) (11 7501.3800904977 3800.9049773756 0.0))
((0 . "LINE") (100 . "AcDbEntity") (8 . "LOUVERS") (62 . 7) (370 . 13) (100 . "AcDbLine") (10 7501.3800904977
3800.9049773756 0.0) (11 7463.6425339367 3800.9049773756 0.0))
((0 . "LINE") (100 . "AcDbEntity") (8 . "LOUVERS") (62 . 7) (370 . 13) (100 . "AcDbLine") (10 7463.6425339367
3800.9049773756 0.0) (11 7424.4909502262 3800.9049773756 0.0))
((0 . "LINE") (100 . "AcDbEntity") (8 . "LOUVERS") (62 . 7) (370 . 13) (100 . "AcDbLine") (10 7424.4909502262
3800.9049773756 0.0) (11 7393.7330316742 3800.9049773756 0.0))
((0 . "LINE") (100 . "AcDbEntity") (8 . "LOUVERS") (62 . 7) (370 . 13) (100 . "AcDbLine") (10 7393.7330316742
3800.9049773756 0.0) (11 7349.9321266968 3800.9049773756 0.0))
((0 . "LINE") (100 . "AcDbEntity") (8 . "LOUVERS") (62 . 7) (370 . 13) (100 . "AcDbLine") (10 7349.9321266968
3800.9049773756 0.0) (11 7322.4321266968 3800.9049773756 0.0))
((0 . "LINE") (100 . "AcDbEntity") (8 . "LOUVERS") (62 . 7) (370 . 13) (100 . "AcDbLine") (10 7322.4321266968
3800.9049773756 0.0) (11 7273.778280543 3800.9049773756 0.0))
((0 . "LINE") (100 . "AcDbEntity") (8 . "LOUVERS") (62 . 7) (370 . 13) (100 . "AcDbLine") (10 7273.778280543
3800.9049773756 0.0) (11 7246.0972850679 3800.9049773756 0.0))
((0 . "LINE") (100 . "AcDbEntity") (8 . "LOUVERS") (62 . 7) (370 . 13) (100 . "AcDbLine") (10 7246.0972850679
3800.9049773756 0.0) (11 7202.0701357466 3800.9049773756 0.0))
((0 . "LINE") (100 . "AcDbEntity") (8 . "LOUVERS") (62 . 7) (370 . 13) (100 . "AcDbLine") (10 7202.0701357466
3800.9049773756 0.0) (11 7172.2058823529 3800.9049773756 0.0))
((0 . "LINE") (100 . "AcDbEntity") (8 . "LOUVERS") (62 . 7) (370 . 13) (100 . "AcDbLine") (10 7172.2058823529
3800.9049773756 0.0) (11 7127.8959276018 3800.9049773756 0.0))
((0 . "LINE") (100 . "AcDbEntity") (8 . "LOUVERS") (62 . 7) (370 . 13) (100 . "AcDbLine") (10 7127.8959276018
3800.9049773756 0.0) (11 7096.7647058824 3800.9049773756 0.0))
((0 . "LINE") (100 . "AcDbEntity") (8 . "LOUVERS") (62 . 7) (370 . 13) (100 . "AcDbLine") (10 7096.7647058824
3800.9049773756 0.0) (11 7047.5113122172 3800.9049773756 0.0))
((0 . "LINE") (100 . "AcDbEntity") (8 . "LOUVERS") (62 . 7) (370 . 13) (100 . "AcDbLine") (10 7047.5113122172
3800.9049773756 0.0) (11 7047.5113122172 5610.8597285068 0.0))
((0 . "LINE") (100 . "AcDbEntity") (8 . "LOUVERS") (62 . 7) (370 . 13) (100 . "AcDbLine") (10 7047.5113122172
5610.8597285068 0.0) (11 7047.5113122172 5712.6696832579 0.0))
((0 . "LINE") (100 . "AcDbEntity") (8 . "LOUVERS") (62 . 7) (370 . 13) (100 . "AcDbLine") (10 7096.7647058824
5712.6696832579 0.0) (11 7096.7647058824 5610.8597285068 0.0))
((0 . "LINE") (100 . "AcDbEntity") (8 . "LOUVERS") (62 . 7) (370 . 13) (100 . "AcDbLine") (10 7096.7647058824
5610.8597285068 0.0) (11 7096.7647058824 3800.9049773756 0.0))
((0 . "LINE") (100 . "AcDbEntity") (8 . "LOUVERS") (62 . 7) (370 . 13) (100 . "AcDbLine") (10 7127.8959276018
5712.6696832579 0.0) (11 7127.8959276018 5610.8597285068 0.0))
((0 . "LINE") (100 . "AcDbEntity") (8 . "LOUVERS") (62 . 7) (370 . 13) (100 . "AcDbLine") (10 7127.8959276018
5610.8597285068 0.0) (11 7127.8959276018 3800.9049773756 0.0))
((0 . "LINE") (100 . "AcDbEntity") (8 . "LOUVERS") (62 . 7) (370 . 13) (100 . "AcDbLine") (10 7172.2058823529
5712.6696832579 0.0) (11 7172.2058823529 5610.8597285068 0.0))
((0 . "LINE") (100 . "AcDbEntity") (8 . "LOUVERS") (62 . 7) (370 . 13) (100 . "AcDbLine") (10 7172.2058823529
5610.8597285068 0.0) (11 7172.2058823529 3800.9049773756 0.0))
((0 . "LINE") (100 . "AcDbEntity") (8 . "LOUVERS") (62 . 7) (370 . 13) (100 . "AcDbLine") (10 7202.0701357466
5712.6696832579 0.0) (11 7202.0701357466 5610.8597285068 0.0))
((0 . "LINE") (100 . "AcDbEntity") (8 . "LOUVERS") (62 . 7) (370 . 13) (100 . "AcDbLine") (10 7202.0701357466
5610.8597285068 0.0) (11 7202.0701357466 3800.9049773756 0.0))
((0 . "LINE") (100 . "AcDbEntity") (8 . "LOUVERS") (62 . 7) (370 . 13) (100 . "AcDbLine") (10 7246.0972850679
5712.6696832579 0.0) (11 7246.0972850679 5610.8597285068 0.0))
((0 . "LINE") (100 . "AcDbEntity") (8 . "LOUVERS") (62 . 7) (370 . 13) (100 . "AcDbLine") (10 7246.0972850679
5610.8597285068 0.0) (11 7246.0972850679 3800.9049773756 0.0))
((0 . "LINE") (100 . "AcDbEntity") (8 . "LOUVERS") (62 . 7) (370 . 13) (100 . "AcDbLine") (10 7273.778280543
5712.6696832579 0.0) (11 7273.778280543 5610.8597285068 0.0))
((0 . "LINE") (100 . "AcDbEntity") (8 . "LOUVERS") (62 . 7) (370 . 13) (100 . "AcDbLine") (10 7273.778280543
5610.8597285068 0.0) (11 7273.778280543 3800.9049773756 0.0))
((0 . "LINE") (100 . "AcDbEntity") (8 . "LOUVERS") (62 . 7) (370 . 13) (100 . "AcDbLine") (10 7322.4321266968
5712.6696832579 0.0) (11 7322.4321266968 5610.8597285068 0.0))
((0 . "LINE") (100 . "AcDbEntity") (8 . "LOUVERS") (62 . 7) (370 . 13) (100 . "AcDbLine") (10 7322.4321266968
5610.8597285068 0.0) (11 7322.4321266968 3800.9049773756 0.0))
((0 . "LINE") (100 . "AcDbEntity") (8 . "LOUVERS") (62 . 7) (370 . 13) (100 . "AcDbLine") (10 7349.9321266968
5712.6696832579 0.0) (11 7349.9321266968 5610.8597285068 0.0))
((0 . "LINE") (100 . "AcDbEntity") (8 . "LOUVERS") (62 . 7) (370 . 13) (100 . "AcDbLine") (10 7349.9321266968
5610.8597285068 0.0) (11 7349.9321266968 3800.9049773756 0.0))
((0 . "LINE") (100 . "AcDbEntity") (8 . "LOUVERS") (62 . 7) (370 . 13) (100 . "AcDbLine") (10 7393.7330316742
5712.6696832579 0.0) (11 7393.7330316742 5610.8597285068 0.0))
((0 . "LINE") (100 . "AcDbEntity") (8 . "LOUVERS") (62 . 7) (370 . 13) (100 . "AcDbLine") (10 7393.7330316742
5610.8597285068 0.0) (11 7393.7330316742 3800.9049773756 0.0))
((0 . "LINE") (100 . "AcDbEntity") (8 . "LOUVERS") (62 . 7) (370 . 13) (100 . "AcDbLine") (10 7424.4909502262
5712.6696832579 0.0) (11 7424.4909502262 5610.8597285068 0.0))
((0 . "LINE") (100 . "AcDbEntity") (8 . "LOUVERS") (62 . 7) (370 . 13) (100 . "AcDbLine") (10 7424.4909502262
5610.8597285068 0.0) (11 7424.4909502262 3800.9049773756 0.0))
((0 . "LINE") (100 . "AcDbEntity") (8 . "LOUVERS") (62 . 7) (370 . 13) (100 . "AcDbLine") (10 7463.6425339367
5712.6696832579 0.0) (11 7463.6425339367 5610.8597285068 0.0))
((0 . "LINE") (100 . "AcDbEntity") (8 . "LOUVERS") (62 . 7) (370 . 13) (100 . "AcDbLine") (10 7463.6425339367
5610.8597285068 0.0) (11 7463.6425339367 3800.9049773756 0.0))
((0 . "LINE") (100 . "AcDbEntity") (8 . "LOUVERS") (62 . 7) (370 . 13) (100 . "AcDbLine") (10 7501.3800904977
5712.6696832579 0.0) (11 7501.3800904977 5610.8597285068 0.0))
((0 . "LINE") (100 . "AcDbEntity") (8 . "LOUVERS") (62 . 7) (370 . 13) (100 . "AcDbLine") (10 7501.3800904977
5610.8597285068 0.0) (11 7501.3800904977 3800.9049773756 0.0))
((0 . "LINE") (100 . "AcDbEntity") (8 . "LOUVERS") (62 . 7) (370 . 13) (100 . "AcDbLine") (10 7529.7171945701
5712.6696832579 0.0) (11 7529.7171945701 5610.8597285068 0.0))
((0 . "LINE") (100 . "AcDbEntity") (8 . "LOUVERS") (62 . 7) (370 . 13) (100 . "AcDbLine") (10 7529.7171945701
5610.8597285068 0.0) (11 7529.7171945701 3800.9049773756 0.0))
((0 . "LINE") (100 . "AcDbEntity") (8 . "LOUVERS") (62 . 7) (370 . 13) (100 . "AcDbLine") (10 4061.0859728507
3212.6696832579 0.0) (11 4105.2036199095 3212.6696832579 0.0))
((0 . "LINE") (100 . "AcDbEntity") (8 . "LOUVERS") (62 . 7) (370 . 13) (100 . "AcDbLine") (10 4105.2036199095
3212.6696832579 0.0) (11 4134.8981900452 3212.6696832579 0.0))
((0 . "LINE") (100 . "AcDbEntity") (8 . "LOUVERS") (62 . 7) (370 . 13) (100 . "AcDbLine") (10 4134.8981900452
3212.6696832579 0.0) (11 4174.5588235294 3212.6696832579 0.0))
((0 . "LINE") (100 . "AcDbEntity") (8 . "LOUVERS") (62 . 7) (370 . 13) (100 . "AcDbLine") (10 4174.5588235294
3212.6696832579 0.0) (11 4207.9411764706 3212.6696832579 0.0))
((0 . "LINE") (100 . "AcDbEntity") (8 . "LOUVERS") (62 . 7) (370 . 13) (100 . "AcDbLine") (10 4207.9411764706
3212.6696832579 0.0) (11 4241.7533936652 3212.6696832579 0.0))
((0 . "LINE") (100 . "AcDbEntity") (8 . "LOUVERS") (62 . 7) (370 . 13) (100 . "AcDbLine") (10 4241.7533936652
3212.6696832579 0.0) (11 4263.0769230769 3212.6696832579 0.0))
((0 . "LINE") (100 . "AcDbEntity") (8 . "LOUVERS") (62 . 7) (370 . 13) (100 . "AcDbLine") (10 4263.0769230769
3212.6696832579 0.0) (11 4297.6583710407 3212.6696832579 0.0))
((0 . "LINE") (100 . "AcDbEntity") (8 . "LOUVERS") (62 . 7) (370 . 13) (100 . "AcDbLine") (10 4297.6583710407
3212.6696832579 0.0) (11 4325.8371040724 3212.6696832579 0.0))
((0 . "LINE") (100 . "AcDbEntity") (8 . "LOUVERS") (62 . 7) (370 . 13) (100 . "AcDbLine") (10 4325.8371040724
3212.6696832579 0.0) (11 4364.0384615385 3212.6696832579 0.0))
((0 . "LINE") (100 . "AcDbEntity") (8 . "LOUVERS") (62 . 7) (370 . 13) (100 . "AcDbLine") (10 4364.0384615385
3212.6696832579 0.0) (11 4399.6153846154 3212.6696832579 0.0))
((0 . "LINE") (100 . "AcDbEntity") (8 . "LOUVERS") (62 . 7) (370 . 13) (100 . "AcDbLine") (10 4399.6153846154
3212.6696832579 0.0) (11 4434.9095022624 3212.6696832579 0.0))
((0 . "LINE") (100 . "AcDbEntity") (8 . "LOUVERS") (62 . 7) (370 . 13) (100 . "AcDbLine") (10 4434.9095022624
3212.6696832579 0.0) (11 4469.8642533937 3212.6696832579 0.0))
((0 . "LINE") (100 . "AcDbEntity") (8 . "LOUVERS") (62 . 7) (370 . 13) (100 . "AcDbLine") (10 4469.8642533937
3212.6696832579 0.0) (11 4505.2714932127 3212.6696832579 0.0))
((0 . "LINE") (100 . "AcDbEntity") (8 . "LOUVERS") (62 . 7) (370 . 13) (100 . "AcDbLine") (10 4505.2714932127
3212.6696832579 0.0) (11 4537.6923076923 3212.6696832579 0.0))
((0 . "LINE") (100 . "AcDbEntity") (8 . "LOUVERS") (62 . 7) (370 . 13) (100 . "AcDbLine") (10 4537.6923076923
3212.6696832579 0.0) (11 4573.4049773756 3212.6696832579 0.0))
((0 . "LINE") (100 . "AcDbEntity") (8 . "LOUVERS") (62 . 7) (370 . 13) (100 . "AcDbLine") (10 4573.4049773756
3212.6696832579 0.0) (11 4604.9095022624 3212.6696832579 0.0))
((0 . "LINE") (100 . "AcDbEntity") (8 . "LOUVERS") (62 . 7) (370 . 13) (100 . "AcDbLine") (10 4604.9095022624
3212.6696832579 0.0) (11 4647.3868778281 3212.6696832579 0.0))
((0 . "LINE") (100 . "AcDbEntity") (8 . "LOUVERS") (62 . 7) (370 . 13) (100 . "AcDbLine") (10 4647.3868778281
3212.6696832579 0.0) (11 4683.665158371 3212.6696832579 0.0))
((0 . "LINE") (100 . "AcDbEntity") (8 . "LOUVERS") (62 . 7) (370 . 13) (100 . "AcDbLine") (10 4683.665158371
3212.6696832579 0.0) (11 4731.2669683258 3212.6696832579 0.0))
((0 . "LINE") (100 . "AcDbEntity") (8 . "LOUVERS") (62 . 7) (370 . 13) (100 . "AcDbLine") (10 4731.2669683258
3212.6696832579 0.0) (11 4749.6040723982 3212.6696832579 0.0))
((0 . "LINE") (100 . "AcDbEntity") (8 . "LOUVERS") (62 . 7) (370 . 13) (100 . "AcDbLine") (10 4749.6040723982
3212.6696832579 0.0) (11 4796.7307692308 3212.6696832579 0.0))
((0 . "LINE") (100 . "AcDbEntity") (8 . "LOUVERS") (62 . 7) (370 . 13) (100 . "AcDbLine") (10 4796.7307692308
3212.6696832579 0.0) (11 4834.0497737557 3212.6696832579 0.0))
((0 . "LINE") (100 . "AcDbEntity") (8 . "LOUVERS") (62 . 7) (370 . 13) (100 . "AcDbLine") (10 4834.0497737557
3212.6696832579 0.0) (11 4861.5271493213 3212.6696832579 0.0))
((0 . "LINE") (100 . "AcDbEntity") (8 . "LOUVERS") (62 . 7) (370 . 13) (100 . "AcDbLine") (10 4861.5271493213
3212.6696832579 0.0) (11 4920.0339366516 3212.6696832579 0.0))
((0 . "LINE") (100 . "AcDbEntity") (8 . "LOUVERS") (62 . 7) (370 . 13) (100 . "AcDbLine") (10 4920.0339366516
3212.6696832579 0.0) (11 4968.1334841629 3212.6696832579 0.0))
((0 . "LINE") (100 . "AcDbEntity") (8 . "LOUVERS") (62 . 7) (370 . 13) (100 . "AcDbLine") (10 4968.1334841629
3212.6696832579 0.0) (11 5002.907239819 3212.6696832579 0.0))
((0 . "LINE") (100 . "AcDbEntity") (8 . "LOUVERS") (62 . 7) (370 . 13) (100 . "AcDbLine") (10 5002.907239819
3212.6696832579 0.0) (11 5042.7375565611 3212.6696832579 0.0))
((0 . "LINE") (100 . "AcDbEntity") (8 . "LOUVERS") (62 . 7) (370 . 13) (100 . "AcDbLine") (10 5042.7375565611
3212.6696832579 0.0) (11 5091.0180995475 3212.6696832579 0.0))
((0 . "LINE") (100 . "AcDbEntity") (8 . "LOUVERS") (62 . 7) (370 . 13) (100 . "AcDbLine") (10 5091.0180995475
3212.6696832579 0.0) (11 5124.7624434389 3212.6696832579 0.0))
((0 . "LINE") (100 . "AcDbEntity") (8 . "LOUVERS") (62 . 7) (370 . 13) (100 . "AcDbLine") (10 5124.7624434389
3212.6696832579 0.0) (11 5162.8619909502 3212.6696832579 0.0))
((0 . "LINE") (100 . "AcDbEntity") (8 . "LOUVERS") (62 . 7) (370 . 13) (100 . "AcDbLine") (10 5162.8619909502
3212.6696832579 0.0) (11 5195.2714932127 3212.6696832579 0.0))
((0 . "LINE") (100 . "AcDbEntity") (8 . "LOUVERS") (62 . 7) (370 . 13) (100 . "AcDbLine") (10 5195.2714932127
3212.6696832579 0.0) (11 5229.9095022624 3212.6696832579 0.0))
((0 . "LINE") (100 . "AcDbEntity") (8 . "LOUVERS") (62 . 7) (370 . 13) (100 . "AcDbLine") (10 5229.9095022624
3212.6696832579 0.0) (11 5262.6583710407 3212.6696832579 0.0))
((0 . "LINE") (100 . "AcDbEntity") (8 . "LOUVERS") (62 . 7) (370 . 13) (100 . "AcDbLine") (10 5262.6583710407
3212.6696832579 0.0) (11 5312.8846153846 3212.6696832579 0.0))
((0 . "LINE") (100 . "AcDbEntity") (8 . "LOUVERS") (62 . 7) (370 . 13) (100 . "AcDbLine") (10 5312.8846153846
3212.6696832579 0.0) (11 5341.3122171946 3212.6696832579 0.0))
((0 . "LINE") (100 . "AcDbEntity") (8 . "LOUVERS") (62 . 7) (370 . 13) (100 . "AcDbLine") (10 5341.3122171946
3212.6696832579 0.0) (11 5388.3484162896 3212.6696832579 0.0))
((0 . "LINE") (100 . "AcDbEntity") (8 . "LOUVERS") (62 . 7) (370 . 13) (100 . "AcDbLine") (10 5388.3484162896
3212.6696832579 0.0) (11 5454.242081448 3212.6696832579 0.0))
((0 . "LINE") (100 . "AcDbEntity") (8 . "LOUVERS") (62 . 7) (370 . 13) (100 . "AcDbLine") (10 5454.242081448
3212.6696832579 0.0) (11 5507.9751131222 3212.6696832579 0.0))
((0 . "LINE") (100 . "AcDbEntity") (8 . "LOUVERS") (62 . 7) (370 . 13) (100 . "AcDbLine") (10 5507.9751131222
3212.6696832579 0.0) (11 5531.1199095023 3212.6696832579 0.0))
((0 . "LINE") (100 . "AcDbEntity") (8 . "LOUVERS") (62 . 7) (370 . 13) (100 . "AcDbLine") (10 5531.1199095023
3212.6696832579 0.0) (11 5574.2194570136 3212.6696832579 0.0))
((0 . "LINE") (100 . "AcDbEntity") (8 . "LOUVERS") (62 . 7) (370 . 13) (100 . "AcDbLine") (10 5574.2194570136
3212.6696832579 0.0) (11 5600.3733031674 3212.6696832579 0.0))
((0 . "LINE") (100 . "AcDbEntity") (8 . "LOUVERS") (62 . 7) (370 . 13) (100 . "AcDbLine") (10 5600.3733031674
3212.6696832579 0.0) (11 5640.3167420814 3212.6696832579 0.0))
((0 . "LINE") (100 . "AcDbEntity") (8 . "LOUVERS") (62 . 7) (370 . 13) (100 . "AcDbLine") (10 5640.3167420814
3212.6696832579 0.0) (11 5675.1131221719 3212.6696832579 0.0))
((0 . "LINE") (100 . "AcDbEntity") (8 . "LOUVERS") (62 . 7) (370 . 13) (100 . "AcDbLine") (10 5675.1131221719
3212.6696832579 0.0) (11 5713.7895927602 3212.6696832579 0.0))
((0 . "LINE") (100 . "AcDbEntity") (8 . "LOUVERS") (62 . 7) (370 . 13) (100 . "AcDbLine") (10 5713.7895927602
3212.6696832579 0.0) (11 5747.2511312217 3212.6696832579 0.0))
((0 . "LINE") (100 . "AcDbEntity") (8 . "LOUVERS") (62 . 7) (370 . 13) (100 . "AcDbLine") (10 5747.2511312217
3212.6696832579 0.0) (11 5780.520361991 3212.6696832579 0.0))
((0 . "LINE") (100 . "AcDbEntity") (8 . "LOUVERS") (62 . 7) (370 . 13) (100 . "AcDbLine") (10 5780.520361991
3212.6696832579 0.0) (11 5816.5610859729 3212.6696832579 0.0))
((0 . "LINE") (100 . "AcDbEntity") (8 . "LOUVERS") (62 . 7) (370 . 13) (100 . "AcDbLine") (10 5816.5610859729
3212.6696832579 0.0) (11 5871.8438914027 3212.6696832579 0.0))
((0 . "LINE") (100 . "AcDbEntity") (8 . "LOUVERS") (62 . 7) (370 . 13) (100 . "AcDbLine") (10 5871.8438914027
3212.6696832579 0.0) (11 5896.4027149321 3212.6696832579 0.0))
((0 . "LINE") (100 . "AcDbEntity") (8 . "LOUVERS") (62 . 7) (370 . 13) (100 . "AcDbLine") (10 5896.4027149321
3212.6696832579 0.0) (11 5935.6561085973 3212.6696832579 0.0))
((0 . "LINE") (100 . "AcDbEntity") (8 . "LOUVERS") (62 . 7) (370 . 13) (100 . "AcDbLine") (10 5935.6561085973
3212.6696832579 0.0) (11 5965.0113122172 3212.6696832579 0.0))
((0 . "LINE") (100 . "AcDbEntity") (8 . "LOUVERS") (62 . 7) (370 . 13) (100 . "AcDbLine") (10 5965.0113122172
3212.6696832579 0.0) (11 6002.4660633484 3212.6696832579 0.0))
((0 . "LINE") (100 . "AcDbEntity") (8 . "LOUVERS") (62 . 7) (370 . 13) (100 . "AcDbLine") (10 6002.4660633484
3212.6696832579 0.0) (11 6036.0180995475 3212.6696832579 0.0))
((0 . "LINE") (100 . "AcDbEntity") (8 . "LOUVERS") (62 . 7) (370 . 13) (100 . "AcDbLine") (10 6036.0180995475
3212.6696832579 0.0) (11 6075.3393665158 3212.6696832579 0.0))
((0 . "LINE") (100 . "AcDbEntity") (8 . "LOUVERS") (62 . 7) (370 . 13) (100 . "AcDbLine") (10 6075.3393665158
3212.6696832579 0.0) (11 6116.2895927602 3212.6696832579 0.0))
((0 . "LINE") (100 . "AcDbEntity") (8 . "LOUVERS") (62 . 7) (370 . 13) (100 . "AcDbLine") (10 6116.2895927602
3212.6696832579 0.0) (11 6147.0701357466 3212.6696832579 0.0))
((0 . "LINE") (100 . "AcDbEntity") (8 . "LOUVERS") (62 . 7) (370 . 13) (100 . "AcDbLine") (10 6147.0701357466
3212.6696832579 0.0) (11 6180.2262443439 3212.6696832579 0.0))
((0 . "LINE") (100 . "AcDbEntity") (8 . "LOUVERS") (62 . 7) (370 . 13) (100 . "AcDbLine") (10 6180.2262443439
3212.6696832579 0.0) (11 6212.6583710407 3212.6696832579 0.0))
((0 . "LINE") (100 . "AcDbEntity") (8 . "LOUVERS") (62 . 7) (370 . 13) (100 . "AcDbLine") (10 6212.6583710407
3212.6696832579 0.0) (11 6246.8212669683 3212.6696832579 0.0))
((0 . "LINE") (100 . "AcDbEntity") (8 . "LOUVERS") (62 . 7) (370 . 13) (100 . "AcDbLine") (10 6246.8212669683
3212.6696832579 0.0) (11 6284.6266968326 3212.6696832579 0.0))
((0 . "LINE") (100 . "AcDbEntity") (8 . "LOUVERS") (62 . 7) (370 . 13) (100 . "AcDbLine") (10 6284.6266968326
3212.6696832579 0.0) (11 6319.8190045249 3212.6696832579 0.0))
((0 . "LINE") (100 . "AcDbEntity") (8 . "LOUVERS") (62 . 7) (370 . 13) (100 . "AcDbLine") (10 6319.8190045249
3212.6696832579 0.0) (11 6348.4049773756 3212.6696832579 0.0))
((0 . "LINE") (100 . "AcDbEntity") (8 . "LOUVERS") (62 . 7) (370 . 13) (100 . "AcDbLine") (10 6348.4049773756
3212.6696832579 0.0) (11 6395.0339366516 3212.6696832579 0.0))
((0 . "LINE") (100 . "AcDbEntity") (8 . "LOUVERS") (62 . 7) (370 . 13) (100 . "AcDbLine") (10 6395.0339366516
3212.6696832579 0.0) (11 6467.8733031674 3212.6696832579 0.0))
((0 . "LINE") (100 . "AcDbEntity") (8 . "LOUVERS") (62 . 7) (370 . 13) (100 . "AcDbLine") (10 6467.8733031674
3212.6696832579 0.0) (11 6489.7285067873 3212.6696832579 0.0))
((0 . "LINE") (100 . "AcDbEntity") (8 . "LOUVERS") (62 . 7) (370 . 13) (100 . "AcDbLine") (10 6489.7285067873
3212.6696832579 0.0) (11 6538.4615384615 3212.6696832579 0.0))
((0 . "LINE") (100 . "AcDbEntity") (8 . "LOUVERS") (62 . 7) (370 . 13) (100 . "AcDbLine") (10 6538.4615384615
3212.6696832579 0.0) (11 6559.0158371041 3212.6696832579 0.0))
((0 . "LINE") (100 . "AcDbEntity") (8 . "LOUVERS") (62 . 7) (370 . 13) (100 . "AcDbLine") (10 6559.0158371041
3212.6696832579 0.0) (11 6604.2194570136 3212.6696832579 0.0))
((0 . "LINE") (100 . "AcDbEntity") (8 . "LOUVERS") (62 . 7) (370 . 13) (100 . "AcDbLine") (10 6604.2194570136
3212.6696832579 0.0) (11 6627.9411764706 3212.6696832579 0.0))
((0 . "LINE") (100 . "AcDbEntity") (8 . "LOUVERS") (62 . 7) (370 . 13) (100 . "AcDbLine") (10 6627.9411764706
3212.6696832579 0.0) (11 6678.2239819005 3212.6696832579 0.0))
((0 . "LINE") (100 . "AcDbEntity") (8 . "LOUVERS") (62 . 7) (370 . 13) (100 . "AcDbLine") (10 6678.2239819005
3212.6696832579 0.0) (11 6709.8303167421 3212.6696832579 0.0))
((0 . "LINE") (100 . "AcDbEntity") (8 . "LOUVERS") (62 . 7) (370 . 13) (100 . "AcDbLine") (10 6709.8303167421
3212.6696832579 0.0) (11 6764.7058823529 3212.6696832579 0.0))
((0 . "LINE") (100 . "AcDbEntity") (8 . "LOUVERS") (62 . 7) (370 . 13) (100 . "AcDbLine") (10 6764.7058823529
3212.6696832579 0.0) (11 6764.7058823529 2952.4886877828 0.0))
((0 . "LINE") (100 . "AcDbEntity") (8 . "LOUVERS") (62 . 7) (370 . 13) (100 . "AcDbLine") (10 6764.7058823529
2952.4886877828 0.0) (11 6709.8303167421 2952.4886877828 0.0))
((0 . "LINE") (100 . "AcDbEntity") (8 . "LOUVERS") (62 . 7) (370 . 13) (100 . "AcDbLine") (10 6709.8303167421
2952.4886877828 0.0) (11 6678.2239819005 2952.4886877828 0.0))
((0 . "LINE") (100 . "AcDbEntity") (8 . "LOUVERS") (62 . 7) (370 . 13) (100 . "AcDbLine") (10 6678.2239819005
2952.4886877828 0.0) (11 6627.9411764706 2952.4886877828 0.0))
((0 . "LINE") (100 . "AcDbEntity") (8 . "LOUVERS") (62 . 7) (370 . 13) (100 . "AcDbLine") (10 6627.9411764706
2952.4886877828 0.0) (11 6604.2194570136 2952.4886877828 0.0))
((0 . "LINE") (100 . "AcDbEntity") (8 . "LOUVERS") (62 . 7) (370 . 13) (100 . "AcDbLine") (10 6604.2194570136
2952.4886877828 0.0) (11 6559.0158371041 2952.4886877828 0.0))
((0 . "LINE") (100 . "AcDbEntity") (8 . "LOUVERS") (62 . 7) (370 . 13) (100 . "AcDbLine") (10 6559.0158371041
2952.4886877828 0.0) (11 6538.4615384615 2952.4886877828 0.0))
((0 . "LINE") (100 . "AcDbEntity") (8 . "LOUVERS") (62 . 7) (370 . 13) (100 . "AcDbLine") (10 6538.4615384615
2952.4886877828 0.0) (11 6489.7285067873 2952.4886877828 0.0))
((0 . "LINE") (100 . "AcDbEntity") (8 . "LOUVERS") (62 . 7) (370 . 13) (100 . "AcDbLine") (10 6489.7285067873
2952.4886877828 0.0) (11 6467.8733031674 2952.4886877828 0.0))
((0 . "LINE") (100 . "AcDbEntity") (8 . "LOUVERS") (62 . 7) (370 . 13) (100 . "AcDbLine") (10 6467.8733031674
2952.4886877828 0.0) (11 6395.0339366516 2952.4886877828 0.0))
((0 . "LINE") (100 . "AcDbEntity") (8 . "LOUVERS") (62 . 7) (370 . 13) (100 . "AcDbLine") (10 6395.0339366516
2952.4886877828 0.0) (11 6348.4049773756 2952.4886877828 0.0))
((0 . "LINE") (100 . "AcDbEntity") (8 . "LOUVERS") (62 . 7) (370 . 13) (100 . "AcDbLine") (10 6348.4049773756
2952.4886877828 0.0) (11 6319.8190045249 2952.4886877828 0.0))
((0 . "LINE") (100 . "AcDbEntity") (8 . "LOUVERS") (62 . 7) (370 . 13) (100 . "AcDbLine") (10 6319.8190045249
2952.4886877828 0.0) (11 6284.6266968326 2952.4886877828 0.0))
((0 . "LINE") (100 . "AcDbEntity") (8 . "LOUVERS") (62 . 7) (370 . 13) (100 . "AcDbLine") (10 6284.6266968326
2952.4886877828 0.0) (11 6246.8212669683 2952.4886877828 0.0))
((0 . "LINE") (100 . "AcDbEntity") (8 . "LOUVERS") (62 . 7) (370 . 13) (100 . "AcDbLine") (10 6246.8212669683
2952.4886877828 0.0) (11 6212.6583710407 2952.4886877828 0.0))
((0 . "LINE") (100 . "AcDbEntity") (8 . "LOUVERS") (62 . 7) (370 . 13) (100 . "AcDbLine") (10 6212.6583710407
2952.4886877828 0.0) (11 6180.2262443439 2952.4886877828 0.0))
((0 . "LINE") (100 . "AcDbEntity") (8 . "LOUVERS") (62 . 7) (370 . 13) (100 . "AcDbLine") (10 6180.2262443439
2952.4886877828 0.0) (11 6147.0701357466 2952.4886877828 0.0))
((0 . "LINE") (100 . "AcDbEntity") (8 . "LOUVERS") (62 . 7) (370 . 13) (100 . "AcDbLine") (10 6147.0701357466
2952.4886877828 0.0) (11 6116.2895927602 2952.4886877828 0.0))
((0 . "LINE") (100 . "AcDbEntity") (8 . "LOUVERS") (62 . 7) (370 . 13) (100 . "AcDbLine") (10 6116.2895927602
2952.4886877828 0.0) (11 6075.3393665158 2952.4886877828 0.0))
((0 . "LINE") (100 . "AcDbEntity") (8 . "LOUVERS") (62 . 7) (370 . 13) (100 . "AcDbLine") (10 6075.3393665158
2952.4886877828 0.0) (11 6036.0180995475 2952.4886877828 0.0))
((0 . "LINE") (100 . "AcDbEntity") (8 . "LOUVERS") (62 . 7) (370 . 13) (100 . "AcDbLine") (10 6036.0180995475
2952.4886877828 0.0) (11 6002.4660633484 2952.4886877828 0.0))
((0 . "LINE") (100 . "AcDbEntity") (8 . "LOUVERS") (62 . 7) (370 . 13) (100 . "AcDbLine") (10 6002.4660633484
2952.4886877828 0.0) (11 5965.0113122172 2952.4886877828 0.0))
((0 . "LINE") (100 . "AcDbEntity") (8 . "LOUVERS") (62 . 7) (370 . 13) (100 . "AcDbLine") (10 5965.0113122172
2952.4886877828 0.0) (11 5935.6561085973 2952.4886877828 0.0))
((0 . "LINE") (100 . "AcDbEntity") (8 . "LOUVERS") (62 . 7) (370 . 13) (100 . "AcDbLine") (10 5935.6561085973
2952.4886877828 0.0) (11 5896.4027149321 2952.4886877828 0.0))
((0 . "LINE") (100 . "AcDbEntity") (8 . "LOUVERS") (62 . 7) (370 . 13) (100 . "AcDbLine") (10 5896.4027149321
2952.4886877828 0.0) (11 5871.8438914027 2952.4886877828 0.0))
((0 . "LINE") (100 . "AcDbEntity") (8 . "LOUVERS") (62 . 7) (370 . 13) (100 . "AcDbLine") (10 5871.8438914027
2952.4886877828 0.0) (11 5816.5610859729 2952.4886877828 0.0))
((0 . "LINE") (100 . "AcDbEntity") (8 . "LOUVERS") (62 . 7) (370 . 13) (100 . "AcDbLine") (10 5816.5610859729
2952.4886877828 0.0) (11 5780.520361991 2952.4886877828 0.0))
((0 . "LINE") (100 . "AcDbEntity") (8 . "LOUVERS") (62 . 7) (370 . 13) (100 . "AcDbLine") (10 5780.520361991
2952.4886877828 0.0) (11 5747.2511312217 2952.4886877828 0.0))
((0 . "LINE") (100 . "AcDbEntity") (8 . "LOUVERS") (62 . 7) (370 . 13) (100 . "AcDbLine") (10 5747.2511312217
2952.4886877828 0.0) (11 5713.7895927602 2952.4886877828 0.0))
((0 . "LINE") (100 . "AcDbEntity") (8 . "LOUVERS") (62 . 7) (370 . 13) (100 . "AcDbLine") (10 5713.7895927602
2952.4886877828 0.0) (11 5675.1131221719 2952.4886877828 0.0))
((0 . "LINE") (100 . "AcDbEntity") (8 . "LOUVERS") (62 . 7) (370 . 13) (100 . "AcDbLine") (10 5675.1131221719
2952.4886877828 0.0) (11 5640.3167420814 2952.4886877828 0.0))
((0 . "LINE") (100 . "AcDbEntity") (8 . "LOUVERS") (62 . 7) (370 . 13) (100 . "AcDbLine") (10 5640.3167420814
2952.4886877828 0.0) (11 5600.3733031674 2952.4886877828 0.0))
((0 . "LINE") (100 . "AcDbEntity") (8 . "LOUVERS") (62 . 7) (370 . 13) (100 . "AcDbLine") (10 5600.3733031674
2952.4886877828 0.0) (11 5574.2194570136 2952.4886877828 0.0))
((0 . "LINE") (100 . "AcDbEntity") (8 . "LOUVERS") (62 . 7) (370 . 13) (100 . "AcDbLine") (10 5574.2194570136
2952.4886877828 0.0) (11 5531.1199095023 2952.4886877828 0.0))
((0 . "LINE") (100 . "AcDbEntity") (8 . "LOUVERS") (62 . 7) (370 . 13) (100 . "AcDbLine") (10 5531.1199095023
2952.4886877828 0.0) (11 5507.9751131222 2952.4886877828 0.0))
((0 . "LINE") (100 . "AcDbEntity") (8 . "LOUVERS") (62 . 7) (370 . 13) (100 . "AcDbLine") (10 5507.9751131222
2952.4886877828 0.0) (11 5454.242081448 2952.4886877828 0.0))
((0 . "LINE") (100 . "AcDbEntity") (8 . "LOUVERS") (62 . 7) (370 . 13) (100 . "AcDbLine") (10 5454.242081448
2952.4886877828 0.0) (11 5388.3484162896 2952.4886877828 0.0))
((0 . "LINE") (100 . "AcDbEntity") (8 . "LOUVERS") (62 . 7) (370 . 13) (100 . "AcDbLine") (10 5388.3484162896
2952.4886877828 0.0) (11 5341.3122171946 2952.4886877828 0.0))
((0 . "LINE") (100 . "AcDbEntity") (8 . "LOUVERS") (62 . 7) (370 . 13) (100 . "AcDbLine") (10 5341.3122171946
2952.4886877828 0.0) (11 5312.8846153846 2952.4886877828 0.0))
((0 . "LINE") (100 . "AcDbEntity") (8 . "LOUVERS") (62 . 7) (370 . 13) (100 . "AcDbLine") (10 5312.8846153846
2952.4886877828 0.0) (11 5262.6583710407 2952.4886877828 0.0))
((0 . "LINE") (100 . "AcDbEntity") (8 . "LOUVERS") (62 . 7) (370 . 13) (100 . "AcDbLine") (10 5262.6583710407
2952.4886877828 0.0) (11 5229.9095022624 2952.4886877828 0.0))
((0 . "LINE") (100 . "AcDbEntity") (8 . "LOUVERS") (62 . 7) (370 . 13) (100 . "AcDbLine") (10 5229.9095022624
2952.4886877828 0.0) (11 5195.2714932127 2952.4886877828 0.0))
((0 . "LINE") (100 . "AcDbEntity") (8 . "LOUVERS") (62 . 7) (370 . 13) (100 . "AcDbLine") (10 5195.2714932127
2952.4886877828 0.0) (11 5162.8619909502 2952.4886877828 0.0))
((0 . "LINE") (100 . "AcDbEntity") (8 . "LOUVERS") (62 . 7) (370 . 13) (100 . "AcDbLine") (10 5162.8619909502
2952.4886877828 0.0) (11 5124.7624434389 2952.4886877828 0.0))
((0 . "LINE") (100 . "AcDbEntity") (8 . "LOUVERS") (62 . 7) (370 . 13) (100 . "AcDbLine") (10 5124.7624434389
2952.4886877828 0.0) (11 5091.0180995475 2952.4886877828 0.0))
((0 . "LINE") (100 . "AcDbEntity") (8 . "LOUVERS") (62 . 7) (370 . 13) (100 . "AcDbLine") (10 5091.0180995475
2952.4886877828 0.0) (11 5042.7375565611 2952.4886877828 0.0))
((0 . "LINE") (100 . "AcDbEntity") (8 . "LOUVERS") (62 . 7) (370 . 13) (100 . "AcDbLine") (10 5042.7375565611
2952.4886877828 0.0) (11 5002.907239819 2952.4886877828 0.0))
((0 . "LINE") (100 . "AcDbEntity") (8 . "LOUVERS") (62 . 7) (370 . 13) (100 . "AcDbLine") (10 5002.907239819
2952.4886877828 0.0) (11 4968.1334841629 2952.4886877828 0.0))
((0 . "LINE") (100 . "AcDbEntity") (8 . "LOUVERS") (62 . 7) (370 . 13) (100 . "AcDbLine") (10 4968.1334841629
2952.4886877828 0.0) (11 4920.0339366516 2952.4886877828 0.0))
((0 . "LINE") (100 . "AcDbEntity") (8 . "LOUVERS") (62 . 7) (370 . 13) (100 . "AcDbLine") (10 4920.0339366516
2952.4886877828 0.0) (11 4861.5271493213 2952.4886877828 0.0))
((0 . "LINE") (100 . "AcDbEntity") (8 . "LOUVERS") (62 . 7) (370 . 13) (100 . "AcDbLine") (10 4861.5271493213
2952.4886877828 0.0) (11 4834.0497737557 2952.4886877828 0.0))
((0 . "LINE") (100 . "AcDbEntity") (8 . "LOUVERS") (62 . 7) (370 . 13) (100 . "AcDbLine") (10 4834.0497737557
2952.4886877828 0.0) (11 4796.7307692308 2952.4886877828 0.0))
((0 . "LINE") (100 . "AcDbEntity") (8 . "LOUVERS") (62 . 7) (370 . 13) (100 . "AcDbLine") (10 4796.7307692308
2952.4886877828 0.0) (11 4749.6040723982 2952.4886877828 0.0))
((0 . "LINE") (100 . "AcDbEntity") (8 . "LOUVERS") (62 . 7) (370 . 13) (100 . "AcDbLine") (10 4749.6040723982
2952.4886877828 0.0) (11 4731.2669683258 2952.4886877828 0.0))
((0 . "LINE") (100 . "AcDbEntity") (8 . "LOUVERS") (62 . 7) (370 . 13) (100 . "AcDbLine") (10 4731.2669683258
2952.4886877828 0.0) (11 4683.665158371 2952.4886877828 0.0))
((0 . "LINE") (100 . "AcDbEntity") (8 . "LOUVERS") (62 . 7) (370 . 13) (100 . "AcDbLine") (10 4683.665158371
2952.4886877828 0.0) (11 4647.3868778281 2952.4886877828 0.0))
((0 . "LINE") (100 . "AcDbEntity") (8 . "LOUVERS") (62 . 7) (370 . 13) (100 . "AcDbLine") (10 4647.3868778281
2952.4886877828 0.0) (11 4604.9095022624 2952.4886877828 0.0))
((0 . "LINE") (100 . "AcDbEntity") (8 . "LOUVERS") (62 . 7) (370 . 13) (100 . "AcDbLine") (10 4604.9095022624
2952.4886877828 0.0) (11 4573.4049773756 2952.4886877828 0.0))
((0 . "LINE") (100 . "AcDbEntity") (8 . "LOUVERS") (62 . 7) (370 . 13) (100 . "AcDbLine") (10 4573.4049773756
2952.4886877828 0.0) (11 4537.6923076923 2952.4886877828 0.0))
((0 . "LINE") (100 . "AcDbEntity") (8 . "LOUVERS") (62 . 7) (370 . 13) (100 . "AcDbLine") (10 4537.6923076923
2952.4886877828 0.0) (11 4505.2714932127 2952.4886877828 0.0))
((0 . "LINE") (100 . "AcDbEntity") (8 . "LOUVERS") (62 . 7) (370 . 13) (100 . "AcDbLine") (10 4505.2714932127
2952.4886877828 0.0) (11 4469.8642533937 2952.4886877828 0.0))
((0 . "LINE") (100 . "AcDbEntity") (8 . "LOUVERS") (62 . 7) (370 . 13) (100 . "AcDbLine") (10 4469.8642533937
2952.4886877828 0.0) (11 4434.9095022624 2952.4886877828 0.0))
((0 . "LINE") (100 . "AcDbEntity") (8 . "LOUVERS") (62 . 7) (370 . 13) (100 . "AcDbLine") (10 4434.9095022624
2952.4886877828 0.0) (11 4399.6153846154 2952.4886877828 0.0))
((0 . "LINE") (100 . "AcDbEntity") (8 . "LOUVERS") (62 . 7) (370 . 13) (100 . "AcDbLine") (10 4399.6153846154
2952.4886877828 0.0) (11 4364.0384615385 2952.4886877828 0.0))
((0 . "LINE") (100 . "AcDbEntity") (8 . "LOUVERS") (62 . 7) (370 . 13) (100 . "AcDbLine") (10 4364.0384615385
2952.4886877828 0.0) (11 4325.8371040724 2952.4886877828 0.0))
((0 . "LINE") (100 . "AcDbEntity") (8 . "LOUVERS") (62 . 7) (370 . 13) (100 . "AcDbLine") (10 4325.8371040724
2952.4886877828 0.0) (11 4297.6583710407 2952.4886877828 0.0))
((0 . "LINE") (100 . "AcDbEntity") (8 . "LOUVERS") (62 . 7) (370 . 13) (100 . "AcDbLine") (10 4297.6583710407
2952.4886877828 0.0) (11 4263.0769230769 2952.4886877828 0.0))
((0 . "LINE") (100 . "AcDbEntity") (8 . "LOUVERS") (62 . 7) (370 . 13) (100 . "AcDbLine") (10 4263.0769230769
2952.4886877828 0.0) (11 4241.7533936652 2952.4886877828 0.0))
((0 . "LINE") (100 . "AcDbEntity") (8 . "LOUVERS") (62 . 7) (370 . 13) (100 . "AcDbLine") (10 4241.7533936652
2952.4886877828 0.0) (11 4207.9411764706 2952.4886877828 0.0))
((0 . "LINE") (100 . "AcDbEntity") (8 . "LOUVERS") (62 . 7) (370 . 13) (100 . "AcDbLine") (10 4207.9411764706
2952.4886877828 0.0) (11 4174.5588235294 2952.4886877828 0.0))
((0 . "LINE") (100 . "AcDbEntity") (8 . "LOUVERS") (62 . 7) (370 . 13) (100 . "AcDbLine") (10 4174.5588235294
2952.4886877828 0.0) (11 4134.8981900452 2952.4886877828 0.0))
((0 . "LINE") (100 . "AcDbEntity") (8 . "LOUVERS") (62 . 7) (370 . 13) (100 . "AcDbLine") (10 4134.8981900452
2952.4886877828 0.0) (11 4105.2036199095 2952.4886877828 0.0))
((0 . "LINE") (100 . "AcDbEntity") (8 . "LOUVERS") (62 . 7) (370 . 13) (100 . "AcDbLine") (10 4105.2036199095
2952.4886877828 0.0) (11 4061.0859728507 2952.4886877828 0.0))
((0 . "LINE") (100 . "AcDbEntity") (8 . "LOUVERS") (62 . 7) (370 . 13) (100 . "AcDbLine") (10 4061.0859728507
2952.4886877828 0.0) (11 4061.0859728507 3212.6696832579 0.0))
((0 . "LINE") (100 . "AcDbEntity") (8 . "LOUVERS") (62 . 7) (370 . 13) (100 . "AcDbLine") (10 4105.2036199095
3212.6696832579 0.0) (11 4105.2036199095 2952.4886877828 0.0))
((0 . "LINE") (100 . "AcDbEntity") (8 . "LOUVERS") (62 . 7) (370 . 13) (100 . "AcDbLine") (10 4134.8981900452
3212.6696832579 0.0) (11 4134.8981900452 2952.4886877828 0.0))
((0 . "LINE") (100 . "AcDbEntity") (8 . "LOUVERS") (62 . 7) (370 . 13) (100 . "AcDbLine") (10 4174.5588235294
3212.6696832579 0.0) (11 4174.5588235294 2952.4886877828 0.0))
((0 . "LINE") (100 . "AcDbEntity") (8 . "LOUVERS") (62 . 7) (370 . 13) (100 . "AcDbLine") (10 4207.9411764706
3212.6696832579 0.0) (11 4207.9411764706 2952.4886877828 0.0))
((0 . "LINE") (100 . "AcDbEntity") (8 . "LOUVERS") (62 . 7) (370 . 13) (100 . "AcDbLine") (10 4241.7533936652
3212.6696832579 0.0) (11 4241.7533936652 2952.4886877828 0.0))
((0 . "LINE") (100 . "AcDbEntity") (8 . "LOUVERS") (62 . 7) (370 . 13) (100 . "AcDbLine") (10 4263.0769230769
3212.6696832579 0.0) (11 4263.0769230769 2952.4886877828 0.0))
((0 . "LINE") (100 . "AcDbEntity") (8 . "LOUVERS") (62 . 7) (370 . 13) (100 . "AcDbLine") (10 4297.6583710407
3212.6696832579 0.0) (11 4297.6583710407 2952.4886877828 0.0))
((0 . "LINE") (100 . "AcDbEntity") (8 . "LOUVERS") (62 . 7) (370 . 13) (100 . "AcDbLine") (10 4325.8371040724
3212.6696832579 0.0) (11 4325.8371040724 2952.4886877828 0.0))
((0 . "LINE") (100 . "AcDbEntity") (8 . "LOUVERS") (62 . 7) (370 . 13) (100 . "AcDbLine") (10 4364.0384615385
3212.6696832579 0.0) (11 4364.0384615385 2952.4886877828 0.0))
((0 . "LINE") (100 . "AcDbEntity") (8 . "LOUVERS") (62 . 7) (370 . 13) (100 . "AcDbLine") (10 4399.6153846154
3212.6696832579 0.0) (11 4399.6153846154 2952.4886877828 0.0))
((0 . "LINE") (100 . "AcDbEntity") (8 . "LOUVERS") (62 . 7) (370 . 13) (100 . "AcDbLine") (10 4434.9095022624
3212.6696832579 0.0) (11 4434.9095022624 2952.4886877828 0.0))
((0 . "LINE") (100 . "AcDbEntity") (8 . "LOUVERS") (62 . 7) (370 . 13) (100 . "AcDbLine") (10 4469.8642533937
3212.6696832579 0.0) (11 4469.8642533937 2952.4886877828 0.0))
((0 . "LINE") (100 . "AcDbEntity") (8 . "LOUVERS") (62 . 7) (370 . 13) (100 . "AcDbLine") (10 4505.2714932127
3212.6696832579 0.0) (11 4505.2714932127 2952.4886877828 0.0))
((0 . "LINE") (100 . "AcDbEntity") (8 . "LOUVERS") (62 . 7) (370 . 13) (100 . "AcDbLine") (10 4537.6923076923
3212.6696832579 0.0) (11 4537.6923076923 2952.4886877828 0.0))
((0 . "LINE") (100 . "AcDbEntity") (8 . "LOUVERS") (62 . 7) (370 . 13) (100 . "AcDbLine") (10 4573.4049773756
3212.6696832579 0.0) (11 4573.4049773756 2952.4886877828 0.0))
((0 . "LINE") (100 . "AcDbEntity") (8 . "LOUVERS") (62 . 7) (370 . 13) (100 . "AcDbLine") (10 4604.9095022624
3212.6696832579 0.0) (11 4604.9095022624 2952.4886877828 0.0))
((0 . "LINE") (100 . "AcDbEntity") (8 . "LOUVERS") (62 . 7) (370 . 13) (100 . "AcDbLine") (10 4647.3868778281
3212.6696832579 0.0) (11 4647.3868778281 2952.4886877828 0.0))
((0 . "LINE") (100 . "AcDbEntity") (8 . "LOUVERS") (62 . 7) (370 . 13) (100 . "AcDbLine") (10 4683.665158371
3212.6696832579 0.0) (11 4683.665158371 2952.4886877828 0.0))
((0 . "LINE") (100 . "AcDbEntity") (8 . "LOUVERS") (62 . 7) (370 . 13) (100 . "AcDbLine") (10 4731.2669683258
3212.6696832579 0.0) (11 4731.2669683258 2952.4886877828 0.0))
((0 . "LINE") (100 . "AcDbEntity") (8 . "LOUVERS") (62 . 7) (370 . 13) (100 . "AcDbLine") (10 4749.6040723982
3212.6696832579 0.0) (11 4749.6040723982 2952.4886877828 0.0))
((0 . "LINE") (100 . "AcDbEntity") (8 . "LOUVERS") (62 . 7) (370 . 13) (100 . "AcDbLine") (10 4796.7307692308
3212.6696832579 0.0) (11 4796.7307692308 2952.4886877828 0.0))
((0 . "LINE") (100 . "AcDbEntity") (8 . "LOUVERS") (62 . 7) (370 . 13) (100 . "AcDbLine") (10 4834.0497737557
3212.6696832579 0.0) (11 4834.0497737557 2952.4886877828 0.0))
((0 . "LINE") (100 . "AcDbEntity") (8 . "LOUVERS") (62 . 7) (370 . 13) (100 . "AcDbLine") (10 4861.5271493213
3212.6696832579 0.0) (11 4861.5271493213 2952.4886877828 0.0))
((0 . "LINE") (100 . "AcDbEntity") (8 . "LOUVERS") (62 . 7) (370 . 13) (100 . "AcDbLine") (10 4920.0339366516
3212.6696832579 0.0) (11 4920.0339366516 2952.4886877828 0.0))
((0 . "LINE") (100 . "AcDbEntity") (8 . "LOUVERS") (62 . 7) (370 . 13) (100 . "AcDbLine") (10 4968.1334841629
3212.6696832579 0.0) (11 4968.1334841629 2952.4886877828 0.0))
((0 . "LINE") (100 . "AcDbEntity") (8 . "LOUVERS") (62 . 7) (370 . 13) (100 . "AcDbLine") (10 5002.907239819
3212.6696832579 0.0) (11 5002.907239819 2952.4886877828 0.0))
((0 . "LINE") (100 . "AcDbEntity") (8 . "LOUVERS") (62 . 7) (370 . 13) (100 . "AcDbLine") (10 5042.7375565611
3212.6696832579 0.0) (11 5042.7375565611 2952.4886877828 0.0))
((0 . "LINE") (100 . "AcDbEntity") (8 . "LOUVERS") (62 . 7) (370 . 13) (100 . "AcDbLine") (10 5091.0180995475
3212.6696832579 0.0) (11 5091.0180995475 2952.4886877828 0.0))
((0 . "LINE") (100 . "AcDbEntity") (8 . "LOUVERS") (62 . 7) (370 . 13) (100 . "AcDbLine") (10 5124.7624434389
3212.6696832579 0.0) (11 5124.7624434389 2952.4886877828 0.0))
((0 . "LINE") (100 . "AcDbEntity") (8 . "LOUVERS") (62 . 7) (370 . 13) (100 . "AcDbLine") (10 5162.8619909502
3212.6696832579 0.0) (11 5162.8619909502 2952.4886877828 0.0))
((0 . "LINE") (100 . "AcDbEntity") (8 . "LOUVERS") (62 . 7) (370 . 13) (100 . "AcDbLine") (10 5195.2714932127
3212.6696832579 0.0) (11 5195.2714932127 2952.4886877828 0.0))
((0 . "LINE") (100 . "AcDbEntity") (8 . "LOUVERS") (62 . 7) (370 . 13) (100 . "AcDbLine") (10 5229.9095022624
3212.6696832579 0.0) (11 5229.9095022624 2952.4886877828 0.0))
((0 . "LINE") (100 . "AcDbEntity") (8 . "LOUVERS") (62 . 7) (370 . 13) (100 . "AcDbLine") (10 5262.6583710407
3212.6696832579 0.0) (11 5262.6583710407 2952.4886877828 0.0))
((0 . "LINE") (100 . "AcDbEntity") (8 . "LOUVERS") (62 . 7) (370 . 13) (100 . "AcDbLine") (10 5312.8846153846
3212.6696832579 0.0) (11 5312.8846153846 2952.4886877828 0.0))
((0 . "LINE") (100 . "AcDbEntity") (8 . "LOUVERS") (62 . 7) (370 . 13) (100 . "AcDbLine") (10 5341.3122171946
3212.6696832579 0.0) (11 5341.3122171946 2952.4886877828 0.0))
((0 . "LINE") (100 . "AcDbEntity") (8 . "LOUVERS") (62 . 7) (370 . 13) (100 . "AcDbLine") (10 5388.3484162896
3212.6696832579 0.0) (11 5388.3484162896 2952.4886877828 0.0))
((0 . "LINE") (100 . "AcDbEntity") (8 . "LOUVERS") (62 . 7) (370 . 13) (100 . "AcDbLine") (10 5454.242081448
3212.6696832579 0.0) (11 5454.242081448 2952.4886877828 0.0))
((0 . "LINE") (100 . "AcDbEntity") (8 . "LOUVERS") (62 . 7) (370 . 13) (100 . "AcDbLine") (10 5507.9751131222
3212.6696832579 0.0) (11 5507.9751131222 2952.4886877828 0.0))
((0 . "LINE") (100 . "AcDbEntity") (8 . "LOUVERS") (62 . 7) (370 . 13) (100 . "AcDbLine") (10 5531.1199095023
3212.6696832579 0.0) (11 5531.1199095023 2952.4886877828 0.0))
((0 . "LINE") (100 . "AcDbEntity") (8 . "LOUVERS") (62 . 7) (370 . 13) (100 . "AcDbLine") (10 5574.2194570136
3212.6696832579 0.0) (11 5574.2194570136 2952.4886877828 0.0))
((0 . "LINE") (100 . "AcDbEntity") (8 . "LOUVERS") (62 . 7) (370 . 13) (100 . "AcDbLine") (10 5600.3733031674
3212.6696832579 0.0) (11 5600.3733031674 2952.4886877828 0.0))
((0 . "LINE") (100 . "AcDbEntity") (8 . "LOUVERS") (62 . 7) (370 . 13) (100 . "AcDbLine") (10 5640.3167420814
3212.6696832579 0.0) (11 5640.3167420814 2952.4886877828 0.0))
((0 . "LINE") (100 . "AcDbEntity") (8 . "LOUVERS") (62 . 7) (370 . 13) (100 . "AcDbLine") (10 5675.1131221719
3212.6696832579 0.0) (11 5675.1131221719 2952.4886877828 0.0))
((0 . "LINE") (100 . "AcDbEntity") (8 . "LOUVERS") (62 . 7) (370 . 13) (100 . "AcDbLine") (10 5713.7895927602
3212.6696832579 0.0) (11 5713.7895927602 2952.4886877828 0.0))
((0 . "LINE") (100 . "AcDbEntity") (8 . "LOUVERS") (62 . 7) (370 . 13) (100 . "AcDbLine") (10 5747.2511312217
3212.6696832579 0.0) (11 5747.2511312217 2952.4886877828 0.0))
((0 . "LINE") (100 . "AcDbEntity") (8 . "LOUVERS") (62 . 7) (370 . 13) (100 . "AcDbLine") (10 5780.520361991
3212.6696832579 0.0) (11 5780.520361991 2952.4886877828 0.0))
((0 . "LINE") (100 . "AcDbEntity") (8 . "LOUVERS") (62 . 7) (370 . 13) (100 . "AcDbLine") (10 5816.5610859729
3212.6696832579 0.0) (11 5816.5610859729 2952.4886877828 0.0))
((0 . "LINE") (100 . "AcDbEntity") (8 . "LOUVERS") (62 . 7) (370 . 13) (100 . "AcDbLine") (10 5871.8438914027
3212.6696832579 0.0) (11 5871.8438914027 2952.4886877828 0.0))
((0 . "LINE") (100 . "AcDbEntity") (8 . "LOUVERS") (62 . 7) (370 . 13) (100 . "AcDbLine") (10 5896.4027149321
3212.6696832579 0.0) (11 5896.4027149321 2952.4886877828 0.0))
((0 . "LINE") (100 . "AcDbEntity") (8 . "LOUVERS") (62 . 7) (370 . 13) (100 . "AcDbLine") (10 5935.6561085973
3212.6696832579 0.0) (11 5935.6561085973 2952.4886877828 0.0))
((0 . "LINE") (100 . "AcDbEntity") (8 . "LOUVERS") (62 . 7) (370 . 13) (100 . "AcDbLine") (10 5965.0113122172
3212.6696832579 0.0) (11 5965.0113122172 2952.4886877828 0.0))
((0 . "LINE") (100 . "AcDbEntity") (8 . "LOUVERS") (62 . 7) (370 . 13) (100 . "AcDbLine") (10 6002.4660633484
3212.6696832579 0.0) (11 6002.4660633484 2952.4886877828 0.0))
((0 . "LINE") (100 . "AcDbEntity") (8 . "LOUVERS") (62 . 7) (370 . 13) (100 . "AcDbLine") (10 6036.0180995475
3212.6696832579 0.0) (11 6036.0180995475 2952.4886877828 0.0))
((0 . "LINE") (100 . "AcDbEntity") (8 . "LOUVERS") (62 . 7) (370 . 13) (100 . "AcDbLine") (10 6075.3393665158
3212.6696832579 0.0) (11 6075.3393665158 2952.4886877828 0.0))
((0 . "LINE") (100 . "AcDbEntity") (8 . "LOUVERS") (62 . 7) (370 . 13) (100 . "AcDbLine") (10 6116.2895927602
3212.6696832579 0.0) (11 6116.2895927602 2952.4886877828 0.0))
((0 . "LINE") (100 . "AcDbEntity") (8 . "LOUVERS") (62 . 7) (370 . 13) (100 . "AcDbLine") (10 6147.0701357466
3212.6696832579 0.0) (11 6147.0701357466 2952.4886877828 0.0))
((0 . "LINE") (100 . "AcDbEntity") (8 . "LOUVERS") (62 . 7) (370 . 13) (100 . "AcDbLine") (10 6180.2262443439
3212.6696832579 0.0) (11 6180.2262443439 2952.4886877828 0.0))
((0 . "LINE") (100 . "AcDbEntity") (8 . "LOUVERS") (62 . 7) (370 . 13) (100 . "AcDbLine") (10 6212.6583710407
3212.6696832579 0.0) (11 6212.6583710407 2952.4886877828 0.0))
((0 . "LINE") (100 . "AcDbEntity") (8 . "LOUVERS") (62 . 7) (370 . 13) (100 . "AcDbLine") (10 6246.8212669683
3212.6696832579 0.0) (11 6246.8212669683 2952.4886877828 0.0))
((0 . "LINE") (100 . "AcDbEntity") (8 . "LOUVERS") (62 . 7) (370 . 13) (100 . "AcDbLine") (10 6284.6266968326
3212.6696832579 0.0) (11 6284.6266968326 2952.4886877828 0.0))
((0 . "LINE") (100 . "AcDbEntity") (8 . "LOUVERS") (62 . 7) (370 . 13) (100 . "AcDbLine") (10 6319.8190045249
3212.6696832579 0.0) (11 6319.8190045249 2952.4886877828 0.0))
((0 . "LINE") (100 . "AcDbEntity") (8 . "LOUVERS") (62 . 7) (370 . 13) (100 . "AcDbLine") (10 6348.4049773756
3212.6696832579 0.0) (11 6348.4049773756 2952.4886877828 0.0))
((0 . "LINE") (100 . "AcDbEntity") (8 . "LOUVERS") (62 . 7) (370 . 13) (100 . "AcDbLine") (10 6395.0339366516
3212.6696832579 0.0) (11 6395.0339366516 2952.4886877828 0.0))
((0 . "LINE") (100 . "AcDbEntity") (8 . "LOUVERS") (62 . 7) (370 . 13) (100 . "AcDbLine") (10 6467.8733031674
3212.6696832579 0.0) (11 6467.8733031674 2952.4886877828 0.0))
((0 . "LINE") (100 . "AcDbEntity") (8 . "LOUVERS") (62 . 7) (370 . 13) (100 . "AcDbLine") (10 6489.7285067873
3212.6696832579 0.0) (11 6489.7285067873 2952.4886877828 0.0))
((0 . "LINE") (100 . "AcDbEntity") (8 . "LOUVERS") (62 . 7) (370 . 13) (100 . "AcDbLine") (10 6538.4615384615
3212.6696832579 0.0) (11 6538.4615384615 2952.4886877828 0.0))
((0 . "LINE") (100 . "AcDbEntity") (8 . "LOUVERS") (62 . 7) (370 . 13) (100 . "AcDbLine") (10 6559.0158371041
3212.6696832579 0.0) (11 6559.0158371041 2952.4886877828 0.0))
((0 . "LINE") (100 . "AcDbEntity") (8 . "LOUVERS") (62 . 7) (370 . 13) (100 . "AcDbLine") (10 6604.2194570136
3212.6696832579 0.0) (11 6604.2194570136 2952.4886877828 0.0))
((0 . "LINE") (100 . "AcDbEntity") (8 . "LOUVERS") (62 . 7) (370 . 13) (100 . "AcDbLine") (10 6627.9411764706
3212.6696832579 0.0) (11 6627.9411764706 2952.4886877828 0.0))
((0 . "LINE") (100 . "AcDbEntity") (8 . "LOUVERS") (62 . 7) (370 . 13) (100 . "AcDbLine") (10 6678.2239819005
3212.6696832579 0.0) (11 6678.2239819005 2952.4886877828 0.0))
((0 . "LINE") (100 . "AcDbEntity") (8 . "LOUVERS") (62 . 7) (370 . 13) (100 . "AcDbLine") (10 6709.8303167421
3212.6696832579 0.0) (11 6709.8303167421 2952.4886877828 0.0))
((0 . "LINE") (100 . "AcDbEntity") (8 . "LOUVERS") (62 . 7) (370 . 13) (100 . "AcDbLine") (10 4355.2036199095
2194.5701357466 0.0) (11 4405.5995475113 2194.5701357466 0.0))
((0 . "LINE") (100 . "AcDbEntity") (8 . "LOUVERS") (62 . 7) (370 . 13) (100 . "AcDbLine") (10 4405.5995475113
2194.5701357466 0.0) (11 4435.2488687783 2194.5701357466 0.0))
((0 . "LINE") (100 . "AcDbEntity") (8 . "LOUVERS") (62 . 7) (370 . 13) (100 . "AcDbLine") (10 4435.2488687783
2194.5701357466 0.0) (11 4479.1628959276 2194.5701357466 0.0))
((0 . "LINE") (100 . "AcDbEntity") (8 . "LOUVERS") (62 . 7) (370 . 13) (100 . "AcDbLine") (10 4479.1628959276
2194.5701357466 0.0) (11 4513.9479638009 2194.5701357466 0.0))
((0 . "LINE") (100 . "AcDbEntity") (8 . "LOUVERS") (62 . 7) (370 . 13) (100 . "AcDbLine") (10 4513.9479638009
2194.5701357466 0.0) (11 4546.6968325792 2194.5701357466 0.0))
((0 . "LINE") (100 . "AcDbEntity") (8 . "LOUVERS") (62 . 7) (370 . 13) (100 . "AcDbLine") (10 4546.6968325792
2194.5701357466 0.0) (11 4579.7850678733 2194.5701357466 0.0))
((0 . "LINE") (100 . "AcDbEntity") (8 . "LOUVERS") (62 . 7) (370 . 13) (100 . "AcDbLine") (10 4579.7850678733
2194.5701357466 0.0) (11 4604.8529411765 2194.5701357466 0.0))
((0 . "LINE") (100 . "AcDbEntity") (8 . "LOUVERS") (62 . 7) (370 . 13) (100 . "AcDbLine") (10 4604.8529411765
2194.5701357466 0.0) (11 4641.8438914027 2194.5701357466 0.0))
((0 . "LINE") (100 . "AcDbEntity") (8 . "LOUVERS") (62 . 7) (370 . 13) (100 . "AcDbLine") (10 4641.8438914027
2194.5701357466 0.0) (11 4660.6334841629 2194.5701357466 0.0))
((0 . "LINE") (100 . "AcDbEntity") (8 . "LOUVERS") (62 . 7) (370 . 13) (100 . "AcDbLine") (10 4660.6334841629
2194.5701357466 0.0) (11 4660.6334841629 2183.257918552 0.0))
((0 . "LINE") (100 . "AcDbEntity") (8 . "LOUVERS") (62 . 7) (370 . 13) (100 . "AcDbLine") (10 4660.6334841629
2183.257918552 0.0) (11 4660.6334841629 1125.8115271493 0.0))
((0 . "LINE") (100 . "AcDbEntity") (8 . "LOUVERS") (62 . 7) (370 . 13) (100 . "AcDbLine") (10 4355.2036199095
1247.3207918552 0.0) (11 4355.2036199095 2194.5701357466 0.0))
((0 . "LINE") (100 . "AcDbEntity") (8 . "LOUVERS") (62 . 7) (370 . 13) (100 . "AcDbLine") (10 4405.5995475113
2194.5701357466 0.0) (11 4405.5995475113 1254.8404411765 0.0))
((0 . "LINE") (100 . "AcDbEntity") (8 . "LOUVERS") (62 . 7) (370 . 13) (100 . "AcDbLine") (10 4435.2488687783
2194.5701357466 0.0) (11 4435.2488687783 1232.9935746606 0.0))
((0 . "LINE") (100 . "AcDbEntity") (8 . "LOUVERS") (62 . 7) (370 . 13) (100 . "AcDbLine") (10 4479.1628959276
2194.5701357466 0.0) (11 4479.1628959276 1200.6358710407 0.0))
((0 . "LINE") (100 . "AcDbEntity") (8 . "LOUVERS") (62 . 7) (370 . 13) (100 . "AcDbLine") (10 4513.9479638009
2194.5701357466 0.0) (11 4513.9479638009 1175.0047624434 0.0))
((0 . "LINE") (100 . "AcDbEntity") (8 . "LOUVERS") (62 . 7) (370 . 13) (100 . "AcDbLine") (10 4546.6968325792
2194.5701357466 0.0) (11 4546.6968325792 1150.8740158371 0.0))
((0 . "LINE") (100 . "AcDbEntity") (8 . "LOUVERS") (62 . 7) (370 . 13) (100 . "AcDbLine") (10 4579.7850678733
2194.5701357466 0.0) (11 4579.7850678733 1126.4932126697 0.0))
((0 . "LINE") (100 . "AcDbEntity") (8 . "LOUVERS") (62 . 7) (370 . 13) (100 . "AcDbLine") (10 4604.8529411765
2194.5701357466 0.0) (11 4604.8529411765 1108.834841629 0.0))
((0 . "LINE") (100 . "AcDbEntity") (8 . "LOUVERS") (62 . 7) (370 . 13) (100 . "AcDbLine") (10 4641.8438914027
2194.5701357466 0.0) (11 4641.8438914027 1120.0929524887 0.0))
((0 . "LINE") (100 . "AcDbEntity") (8 . "LOUVERS") (62 . 7) (370 . 13) (100 . "AcDbLine") (10 6210.407239819
2194.5701357466 0.0) (11 6244.6606334842 2194.5701357466 0.0))
((0 . "LINE") (100 . "AcDbEntity") (8 . "LOUVERS") (62 . 7) (370 . 13) (100 . "AcDbLine") (10 6244.6606334842
2194.5701357466 0.0) (11 6285.7013574661 2194.5701357466 0.0))
((0 . "LINE") (100 . "AcDbEntity") (8 . "LOUVERS") (62 . 7) (370 . 13) (100 . "AcDbLine") (10 6285.7013574661
2194.5701357466 0.0) (11 6311.1877828054 2194.5701357466 0.0))
((0 . "LINE") (100 . "AcDbEntity") (8 . "LOUVERS") (62 . 7) (370 . 13) (100 . "AcDbLine") (10 6311.1877828054
2194.5701357466 0.0) (11 6352.6470588235 2194.5701357466 0.0))
((0 . "LINE") (100 . "AcDbEntity") (8 . "LOUVERS") (62 . 7) (370 . 13) (100 . "AcDbLine") (10 6352.6470588235
2194.5701357466 0.0) (11 6379.3325791855 2194.5701357466 0.0))
((0 . "LINE") (100 . "AcDbEntity") (8 . "LOUVERS") (62 . 7) (370 . 13) (100 . "AcDbLine") (10 6379.3325791855
2194.5701357466 0.0) (11 6414.5135746606 2194.5701357466 0.0))
((0 . "LINE") (100 . "AcDbEntity") (8 . "LOUVERS") (62 . 7) (370 . 13) (100 . "AcDbLine") (10 6414.5135746606
2194.5701357466 0.0) (11 6445.5882352941 2194.5701357466 0.0))
((0 . "LINE") (100 . "AcDbEntity") (8 . "LOUVERS") (62 . 7) (370 . 13) (100 . "AcDbLine") (10 6445.5882352941
2194.5701357466 0.0) (11 6492.3416289593 2194.5701357466 0.0))
((0 . "LINE") (100 . "AcDbEntity") (8 . "LOUVERS") (62 . 7) (370 . 13) (100 . "AcDbLine") (10 6492.3416289593
2194.5701357466 0.0) (11 6538.4615384615 2194.5701357466 0.0))
((0 . "LINE") (100 . "AcDbEntity") (8 . "LOUVERS") (62 . 7) (370 . 13) (100 . "AcDbLine") (10 6538.4615384615
2194.5701357466 0.0) (11 6538.4615384615 1171.7075452489 0.0))
((0 . "LINE") (100 . "AcDbEntity") (8 . "LOUVERS") (62 . 7) (370 . 13) (100 . "AcDbLine") (10 6210.407239819
1166.7009502262 0.0) (11 6210.407239819 2183.257918552 0.0))
((0 . "LINE") (100 . "AcDbEntity") (8 . "LOUVERS") (62 . 7) (370 . 13) (100 . "AcDbLine") (10 6210.407239819
2183.257918552 0.0) (11 6210.407239819 2194.5701357466 0.0))
((0 . "LINE") (100 . "AcDbEntity") (8 . "LOUVERS") (62 . 7) (370 . 13) (100 . "AcDbLine") (10 6244.6606334842
2194.5701357466 0.0) (11 6244.6606334842 1190.0555316742 0.0))
((0 . "LINE") (100 . "AcDbEntity") (8 . "LOUVERS") (62 . 7) (370 . 13) (100 . "AcDbLine") (10 6285.7013574661
2194.5701357466 0.0) (11 6285.7013574661 1218.0378393665 0.0))
((0 . "LINE") (100 . "AcDbEntity") (8 . "LOUVERS") (62 . 7) (370 . 13) (100 . "AcDbLine") (10 6311.1877828054
2194.5701357466 0.0) (11 6311.1877828054 1235.4149547511 0.0))
((0 . "LINE") (100 . "AcDbEntity") (8 . "LOUVERS") (62 . 7) (370 . 13) (100 . "AcDbLine") (10 6352.6470588235
2194.5701357466 0.0) (11 6352.6470588235 1263.6826357466 0.0))
((0 . "LINE") (100 . "AcDbEntity") (8 . "LOUVERS") (62 . 7) (370 . 13) (100 . "AcDbLine") (10 6379.3325791855
2194.5701357466 0.0) (11 6379.3325791855 1255.459638009 0.0))
((0 . "LINE") (100 . "AcDbEntity") (8 . "LOUVERS") (62 . 7) (370 . 13) (100 . "AcDbLine") (10 6414.5135746606
2194.5701357466 0.0) (11 6414.5135746606 1236.9433144796 0.0))
((0 . "LINE") (100 . "AcDbEntity") (8 . "LOUVERS") (62 . 7) (370 . 13) (100 . "AcDbLine") (10 6445.5882352941
2194.5701357466 0.0) (11 6445.5882352941 1220.5882352941 0.0))
((0 . "LINE") (100 . "AcDbEntity") (8 . "LOUVERS") (62 . 7) (370 . 13) (100 . "AcDbLine") (10 6492.3416289593
2194.5701357466 0.0) (11 6492.3416289593 1195.9811877828 0.0))
((0 . "LINE") (100 . "AcDbEntity") (8 . "LOUVERS") (62 . 7) (370 . 13) (100 . "AcDbLine") (10 13291.8552036199
5531.6742081448 0.0) (11 13325.7918552036 5531.6742081448 0.0))
((0 . "LINE") (100 . "AcDbEntity") (8 . "LOUVERS") (62 . 7) (370 . 13) (100 . "AcDbLine") (10 13823.5294117647
5531.6742081448 0.0) (11 13823.5294117647 5045.2488687783 0.0))
((0 . "LINE") (100 . "AcDbEntity") (8 . "LOUVERS") (62 . 7) (370 . 13) (100 . "AcDbLine") (10 13823.5294117647
5045.2488687783 0.0) (11 13823.5294117647 4050.1064705882 0.0))
((0 . "LINE") (100 . "AcDbEntity") (8 . "LOUVERS") (62 . 7) (370 . 13) (100 . "AcDbLine") (10 13291.8552036199
4091.2518891403 0.0) (11 13291.8552036199 4208.1447963801 0.0))
((0 . "LINE") (100 . "AcDbEntity") (8 . "LOUVERS") (62 . 7) (370 . 13) (100 . "AcDbLine") (10 13291.8552036199
4314.4796380091 0.0) (11 13291.8552036199 5531.6742081448 0.0))
((0 . "LINE") (100 . "AcDbEntity") (8 . "LOUVERS") (62 . 7) (370 . 13) (100 . "AcDbLine") (10 13326.334841629
5531.6742081448 0.0) (11 13326.334841629 4293.7918552036 0.0))
((0 . "LINE") (100 . "AcDbEntity") (8 . "LOUVERS") (62 . 7) (370 . 13) (100 . "AcDbLine") (10 13386.9230769231
5531.6742081448 0.0) (11 13386.9230769231 4257.4389140271 0.0))
((0 . "LINE") (100 . "AcDbEntity") (8 . "LOUVERS") (62 . 7) (370 . 13) (100 . "AcDbLine") (10 13464.7850678733
5531.6742081448 0.0) (11 13464.7850678733 4210.721719457 0.0))
((0 . "LINE") (100 . "AcDbEntity") (8 . "LOUVERS") (62 . 7) (370 . 13) (100 . "AcDbLine") (10 13480.4524886878
5531.6742081448 0.0) (11 13480.4524886878 4201.3212669683 0.0))
((0 . "LINE") (100 . "AcDbEntity") (8 . "LOUVERS") (62 . 7) (370 . 13) (100 . "AcDbLine") (10 13543.5520361991
5531.6742081448 0.0) (11 13543.5520361991 4238.996300905 0.0))
((0 . "LINE") (100 . "AcDbEntity") (8 . "LOUVERS") (62 . 7) (370 . 13) (100 . "AcDbLine") (10 13625.4524886878
5531.6742081448 0.0) (11 13625.4524886878 4358.1242307692 0.0))
((0 . "LINE") (100 . "AcDbEntity") (8 . "LOUVERS") (62 . 7) (370 . 13) (100 . "AcDbLine") (10 13690.9389140272
5531.6742081448 0.0) (11 13690.9389140272 4222.1992873303 0.0))
((0 . "LINE") (100 . "AcDbEntity") (8 . "LOUVERS") (62 . 7) (370 . 13) (100 . "AcDbLine") (10 13707.8959276018
5531.6742081448 0.0) (11 13707.8959276018 4181.2198303167 0.0))
((0 . "LINE") (100 . "AcDbEntity") (8 . "LOUVERS") (62 . 7) (370 . 13) (100 . "AcDbLine") (10 13772.3755656109
5531.6742081448 0.0) (11 13772.3755656109 4039.5747963801 0.0))
((0 . "LINE") (100 . "AcDbEntity") (8 . "LOUVERS") (62 . 7) (370 . 13) (100 . "AcDbLine") (10 15825.7918552036
5531.6742081448 0.0) (11 15831.9570135747 5531.6742081448 0.0))
((0 . "LINE") (100 . "AcDbEntity") (8 . "LOUVERS") (62 . 7) (370 . 13) (100 . "AcDbLine") (10 15831.9570135747
5531.6742081448 0.0) (11 15859.7285067873 5531.6742081448 0.0))
((0 . "LINE") (100 . "AcDbEntity") (8 . "LOUVERS") (62 . 7) (370 . 13) (100 . "AcDbLine") (10 15859.7285067873
5531.6742081448 0.0) (11 15859.7285067873 4276.0180995475 0.0))
((0 . "LINE") (100 . "AcDbEntity") (8 . "WINDOWS") (62 . 7) (370 . 13) (100 . "AcDbLine") (10 15361.9909502262
4231.9599886878 0.0) (11 15361.9909502262 5045.2488687783 0.0))
((0 . "LINE") (100 . "AcDbEntity") (8 . "LOUVERS") (62 . 7) (370 . 13) (100 . "AcDbLine") (10 15361.9909502262
5045.2488687783 0.0) (11 15361.9909502262 5531.6742081448 0.0))
((0 . "LINE") (100 . "AcDbEntity") (8 . "LOUVERS") (62 . 7) (370 . 13) (100 . "AcDbLine") (10 15421.685520362
5531.6742081448 0.0) (11 15421.685520362 4282.2291063348 0.0))
((0 . "LINE") (100 . "AcDbEntity") (8 . "LOUVERS") (62 . 7) (370 . 13) (100 . "AcDbLine") (10 15438.7104072398
5531.6742081448 0.0) (11 15438.7104072398 4296.5658484163 0.0))
((0 . "LINE") (100 . "AcDbEntity") (8 . "LOUVERS") (62 . 7) (370 . 13) (100 . "AcDbLine") (10 15498.5972850679
5531.6742081448 0.0) (11 15498.5972850679 4323.251459276 0.0))
((0 . "LINE") (100 . "AcDbEntity") (8 . "LOUVERS") (62 . 7) (370 . 13) (100 . "AcDbLine") (10 15516.2895927602
5531.6742081448 0.0) (11 15516.2895927602 4330.8338687783 0.0))
((0 . "LINE") (100 . "AcDbEntity") (8 . "LOUVERS") (62 . 7) (370 . 13) (100 . "AcDbLine") (10 15568.1674208145
5531.6742081448 0.0) (11 15568.1674208145 4353.0672285068 0.0))
((0 . "LINE") (100 . "AcDbEntity") (8 . "LOUVERS") (62 . 7) (370 . 13) (100 . "AcDbLine") (10 15618.9479638009
5531.6742081448 0.0) (11 15618.9479638009 4318.0147058824 0.0))
((0 . "LINE") (100 . "AcDbEntity") (8 . "LOUVERS") (62 . 7) (370 . 13) (100 . "AcDbLine") (10 15681.3461538462
5531.6742081448 0.0) (11 15681.3461538462 4162.0192307692 0.0))
((0 . "LINE") (100 . "AcDbEntity") (8 . "LOUVERS") (62 . 7) (370 . 13) (100 . "AcDbLine") (10 15698.7330316742
5531.6742081448 0.0) (11 15698.7330316742 4147.221719457 0.0))
((0 . "LINE") (100 . "AcDbEntity") (8 . "LOUVERS") (62 . 7) (370 . 13) (100 . "AcDbLine") (10 15748.834841629
5531.6742081448 0.0) (11 15748.834841629 4187.3031674208 0.0))
((0 . "LINE") (100 . "AcDbEntity") (8 . "LOUVERS") (62 . 7) (370 . 13) (100 . "AcDbLine") (10 15775.2941176471
5531.6742081448 0.0) (11 15775.2941176471 4208.4705882353 0.0))
((0 . "LINE") (100 . "AcDbEntity") (8 . "LOUVERS") (62 . 7) (370 . 13) (100 . "AcDbLine") (10 15831.9570135747
5531.6742081448 0.0) (11 15831.9570135747 4253.8009049774 0.0))
((0 . "LINE") (100 . "AcDbEntity") (8 . "LOUVERS") (62 . 7) (370 . 13) (100 . "AcDbLine") (10 12420.814479638
5712.6696832579 0.0) (11 12478.4162895928 5712.6696832579 0.0))
((0 . "LINE") (100 . "AcDbEntity") (8 . "LOUVERS") (62 . 7) (370 . 13) (100 . "AcDbLine") (10 12478.4162895928
5712.6696832579 0.0) (11 12505.7918552036 5712.6696832579 0.0))
((0 . "LINE") (100 . "AcDbEntity") (8 . "LOUVERS") (62 . 7) (370 . 13) (100 . "AcDbLine") (10 12505.7918552036
5712.6696832579 0.0) (11 12552.0022624434 5712.6696832579 0.0))
((0 . "LINE") (100 . "AcDbEntity") (8 . "LOUVERS") (62 . 7) (370 . 13) (100 . "AcDbLine") (10 12552.0022624434
5712.6696832579 0.0) (11 12642.3076923077 5712.6696832579 0.0))
((0 . "LINE") (100 . "AcDbEntity") (8 . "LOUVERS") (62 . 7) (370 . 13) (100 . "AcDbLine") (10 12642.3076923077
5712.6696832579 0.0) (11 12695.1583710407 5712.6696832579 0.0))
((0 . "LINE") (100 . "AcDbEntity") (8 . "LOUVERS") (62 . 7) (370 . 13) (100 . "AcDbLine") (10 12695.1583710407
5712.6696832579 0.0) (11 12711.742081448 5712.6696832579 0.0))
((0 . "LINE") (100 . "AcDbEntity") (8 . "LOUVERS") (62 . 7) (370 . 13) (100 . "AcDbLine") (10 12711.742081448
5712.6696832579 0.0) (11 12761.2556561086 5712.6696832579 0.0))
((0 . "LINE") (100 . "AcDbEntity") (8 . "LOUVERS") (62 . 7) (370 . 13) (100 . "AcDbLine") (10 12761.2556561086
5712.6696832579 0.0) (11 12790.3054298643 5712.6696832579 0.0))
((0 . "LINE") (100 . "AcDbEntity") (8 . "LOUVERS") (62 . 7) (370 . 13) (100 . "AcDbLine") (10 12790.3054298643
5712.6696832579 0.0) (11 12820.2941176471 5712.6696832579 0.0))
((0 . "LINE") (100 . "AcDbEntity") (8 . "LOUVERS") (62 . 7) (370 . 13) (100 . "AcDbLine") (10 12820.2941176471
5712.6696832579 0.0) (11 12864.592760181 5712.6696832579 0.0))
((0 . "LINE") (100 . "AcDbEntity") (8 . "LOUVERS") (62 . 7) (370 . 13) (100 . "AcDbLine") (10 12864.592760181
5712.6696832579 0.0) (11 12883.3936651584 5712.6696832579 0.0))
((0 . "LINE") (100 . "AcDbEntity") (8 . "LOUVERS") (62 . 7) (370 . 13) (100 . "AcDbLine") (10 12883.3936651584
5712.6696832579 0.0) (11 12940.6787330317 5712.6696832579 0.0))
((0 . "LINE") (100 . "AcDbEntity") (8 . "LOUVERS") (62 . 7) (370 . 13) (100 . "AcDbLine") (10 12940.6787330317
5712.6696832579 0.0) (11 12952.4886877828 5712.6696832579 0.0))
((0 . "LINE") (100 . "AcDbEntity") (8 . "LOUVERS") (62 . 7) (370 . 13) (100 . "AcDbLine") (10 12952.4886877828
5712.6696832579 0.0) (11 12952.4886877828 5610.8597285068 0.0))
((0 . "LINE") (100 . "AcDbEntity") (8 . "LOUVERS") (62 . 7) (370 . 13) (100 . "AcDbLine") (10 12952.4886877828
5610.8597285068 0.0) (11 12952.4886877828 3800.9049773756 0.0))
((0 . "LINE") (100 . "AcDbEntity") (8 . "LOUVERS") (62 . 7) (370 . 13) (100 . "AcDbLine") (10 12952.4886877828
3800.9049773756 0.0) (11 12940.6787330317 3800.9049773756 0.0))
((0 . "LINE") (100 . "AcDbEntity") (8 . "LOUVERS") (62 . 7) (370 . 13) (100 . "AcDbLine") (10 12940.6787330317
3800.9049773756 0.0) (11 12883.3936651584 3800.9049773756 0.0))
((0 . "LINE") (100 . "AcDbEntity") (8 . "LOUVERS") (62 . 7) (370 . 13) (100 . "AcDbLine") (10 12883.3936651584
3800.9049773756 0.0) (11 12864.592760181 3800.9049773756 0.0))
((0 . "LINE") (100 . "AcDbEntity") (8 . "LOUVERS") (62 . 7) (370 . 13) (100 . "AcDbLine") (10 12864.592760181
3800.9049773756 0.0) (11 12820.2941176471 3800.9049773756 0.0))
((0 . "LINE") (100 . "AcDbEntity") (8 . "LOUVERS") (62 . 7) (370 . 13) (100 . "AcDbLine") (10 12820.2941176471
3800.9049773756 0.0) (11 12790.3054298643 3800.9049773756 0.0))
((0 . "LINE") (100 . "AcDbEntity") (8 . "LOUVERS") (62 . 7) (370 . 13) (100 . "AcDbLine") (10 12790.3054298643
3800.9049773756 0.0) (11 12761.2556561086 3800.9049773756 0.0))
((0 . "LINE") (100 . "AcDbEntity") (8 . "LOUVERS") (62 . 7) (370 . 13) (100 . "AcDbLine") (10 12761.2556561086
3800.9049773756 0.0) (11 12711.742081448 3800.9049773756 0.0))
((0 . "LINE") (100 . "AcDbEntity") (8 . "LOUVERS") (62 . 7) (370 . 13) (100 . "AcDbLine") (10 12711.742081448
3800.9049773756 0.0) (11 12695.1583710407 3800.9049773756 0.0))
((0 . "LINE") (100 . "AcDbEntity") (8 . "LOUVERS") (62 . 7) (370 . 13) (100 . "AcDbLine") (10 12695.1583710407
3800.9049773756 0.0) (11 12642.3076923077 3800.9049773756 0.0))
((0 . "LINE") (100 . "AcDbEntity") (8 . "LOUVERS") (62 . 7) (370 . 13) (100 . "AcDbLine") (10 12642.3076923077
3800.9049773756 0.0) (11 12552.0022624434 3800.9049773756 0.0))
((0 . "LINE") (100 . "AcDbEntity") (8 . "LOUVERS") (62 . 7) (370 . 13) (100 . "AcDbLine") (10 12552.0022624434
3800.9049773756 0.0) (11 12505.7918552036 3800.9049773756 0.0))
((0 . "LINE") (100 . "AcDbEntity") (8 . "LOUVERS") (62 . 7) (370 . 13) (100 . "AcDbLine") (10 12505.7918552036
3800.9049773756 0.0) (11 12478.4162895928 3800.9049773756 0.0))
((0 . "LINE") (100 . "AcDbEntity") (8 . "LOUVERS") (62 . 7) (370 . 13) (100 . "AcDbLine") (10 12478.4162895928
3800.9049773756 0.0) (11 12420.814479638 3800.9049773756 0.0))
((0 . "LINE") (100 . "AcDbEntity") (8 . "LOUVERS") (62 . 7) (370 . 13) (100 . "AcDbLine") (10 12420.814479638
3800.9049773756 0.0) (11 12420.814479638 5610.8597285068 0.0))
((0 . "LINE") (100 . "AcDbEntity") (8 . "LOUVERS") (62 . 7) (370 . 13) (100 . "AcDbLine") (10 12420.814479638
5610.8597285068 0.0) (11 12420.814479638 5712.6696832579 0.0))
((0 . "LINE") (100 . "AcDbEntity") (8 . "LOUVERS") (62 . 7) (370 . 13) (100 . "AcDbLine") (10 12478.4162895928
5712.6696832579 0.0) (11 12478.4162895928 5610.8597285068 0.0))
((0 . "LINE") (100 . "AcDbEntity") (8 . "LOUVERS") (62 . 7) (370 . 13) (100 . "AcDbLine") (10 12478.4162895928
5610.8597285068 0.0) (11 12478.4162895928 3800.9049773756 0.0))
((0 . "LINE") (100 . "AcDbEntity") (8 . "LOUVERS") (62 . 7) (370 . 13) (100 . "AcDbLine") (10 12505.7918552036
5712.6696832579 0.0) (11 12505.7918552036 5610.8597285068 0.0))
((0 . "LINE") (100 . "AcDbEntity") (8 . "LOUVERS") (62 . 7) (370 . 13) (100 . "AcDbLine") (10 12505.7918552036
5610.8597285068 0.0) (11 12505.7918552036 3800.9049773756 0.0))
((0 . "LINE") (100 . "AcDbEntity") (8 . "LOUVERS") (62 . 7) (370 . 13) (100 . "AcDbLine") (10 12552.0022624434
5712.6696832579 0.0) (11 12552.0022624434 5610.8597285068 0.0))
((0 . "LINE") (100 . "AcDbEntity") (8 . "LOUVERS") (62 . 7) (370 . 13) (100 . "AcDbLine") (10 12552.0022624434
5610.8597285068 0.0) (11 12552.0022624434 3800.9049773756 0.0))
((0 . "LINE") (100 . "AcDbEntity") (8 . "LOUVERS") (62 . 7) (370 . 13) (100 . "AcDbLine") (10 12642.3076923077
5712.6696832579 0.0) (11 12642.3076923077 5610.8597285068 0.0))
((0 . "LINE") (100 . "AcDbEntity") (8 . "LOUVERS") (62 . 7) (370 . 13) (100 . "AcDbLine") (10 12642.3076923077
5610.8597285068 0.0) (11 12642.3076923077 3800.9049773756 0.0))
((0 . "LINE") (100 . "AcDbEntity") (8 . "LOUVERS") (62 . 7) (370 . 13) (100 . "AcDbLine") (10 12695.1583710407
5712.6696832579 0.0) (11 12695.1583710407 5610.8597285068 0.0))
((0 . "LINE") (100 . "AcDbEntity") (8 . "LOUVERS") (62 . 7) (370 . 13) (100 . "AcDbLine") (10 12695.1583710407
5610.8597285068 0.0) (11 12695.1583710407 3800.9049773756 0.0))
((0 . "LINE") (100 . "AcDbEntity") (8 . "LOUVERS") (62 . 7) (370 . 13) (100 . "AcDbLine") (10 12711.742081448
5712.6696832579 0.0) (11 12711.742081448 5610.8597285068 0.0))
((0 . "LINE") (100 . "AcDbEntity") (8 . "LOUVERS") (62 . 7) (370 . 13) (100 . "AcDbLine") (10 12711.742081448
5610.8597285068 0.0) (11 12711.742081448 3800.9049773756 0.0))
((0 . "LINE") (100 . "AcDbEntity") (8 . "LOUVERS") (62 . 7) (370 . 13) (100 . "AcDbLine") (10 12761.2556561086
5712.6696832579 0.0) (11 12761.2556561086 5610.8597285068 0.0))
((0 . "LINE") (100 . "AcDbEntity") (8 . "LOUVERS") (62 . 7) (370 . 13) (100 . "AcDbLine") (10 12761.2556561086
5610.8597285068 0.0) (11 12761.2556561086 3800.9049773756 0.0))
((0 . "LINE") (100 . "AcDbEntity") (8 . "LOUVERS") (62 . 7) (370 . 13) (100 . "AcDbLine") (10 12790.3054298643
5712.6696832579 0.0) (11 12790.3054298643 5610.8597285068 0.0))
((0 . "LINE") (100 . "AcDbEntity") (8 . "LOUVERS") (62 . 7) (370 . 13) (100 . "AcDbLine") (10 12790.3054298643
5610.8597285068 0.0) (11 12790.3054298643 3800.9049773756 0.0))
((0 . "LINE") (100 . "AcDbEntity") (8 . "LOUVERS") (62 . 7) (370 . 13) (100 . "AcDbLine") (10 12820.2941176471
5712.6696832579 0.0) (11 12820.2941176471 5610.8597285068 0.0))
((0 . "LINE") (100 . "AcDbEntity") (8 . "LOUVERS") (62 . 7) (370 . 13) (100 . "AcDbLine") (10 12820.2941176471
5610.8597285068 0.0) (11 12820.2941176471 3800.9049773756 0.0))
((0 . "LINE") (100 . "AcDbEntity") (8 . "LOUVERS") (62 . 7) (370 . 13) (100 . "AcDbLine") (10 12864.592760181
5712.6696832579 0.0) (11 12864.592760181 5610.8597285068 0.0))
((0 . "LINE") (100 . "AcDbEntity") (8 . "LOUVERS") (62 . 7) (370 . 13) (100 . "AcDbLine") (10 12864.592760181
5610.8597285068 0.0) (11 12864.592760181 3800.9049773756 0.0))
((0 . "LINE") (100 . "AcDbEntity") (8 . "LOUVERS") (62 . 7) (370 . 13) (100 . "AcDbLine") (10 12883.3936651584
5712.6696832579 0.0) (11 12883.3936651584 5610.8597285068 0.0))
((0 . "LINE") (100 . "AcDbEntity") (8 . "LOUVERS") (62 . 7) (370 . 13) (100 . "AcDbLine") (10 12883.3936651584
5610.8597285068 0.0) (11 12883.3936651584 3800.9049773756 0.0))
((0 . "LINE") (100 . "AcDbEntity") (8 . "LOUVERS") (62 . 7) (370 . 13) (100 . "AcDbLine") (10 12940.6787330317
5712.6696832579 0.0) (11 12940.6787330317 5610.8597285068 0.0))
((0 . "LINE") (100 . "AcDbEntity") (8 . "LOUVERS") (62 . 7) (370 . 13) (100 . "AcDbLine") (10 12940.6787330317
5610.8597285068 0.0) (11 12940.6787330317 3800.9049773756 0.0))
((0 . "LINE") (100 . "AcDbEntity") (8 . "LOUVERS") (62 . 7) (370 . 13) (100 . "AcDbLine") (10 16221.7194570136
5712.6696832579 0.0) (11 16274.2986425339 5712.6696832579 0.0))
((0 . "LINE") (100 . "AcDbEntity") (8 . "LOUVERS") (62 . 7) (370 . 13) (100 . "AcDbLine") (10 16274.2986425339
5712.6696832579 0.0) (11 16301.6063348416 5712.6696832579 0.0))
((0 . "LINE") (100 . "AcDbEntity") (8 . "LOUVERS") (62 . 7) (370 . 13) (100 . "AcDbLine") (10 16301.6063348416
5712.6696832579 0.0) (11 16348.3823529412 5712.6696832579 0.0))
((0 . "LINE") (100 . "AcDbEntity") (8 . "LOUVERS") (62 . 7) (370 . 13) (100 . "AcDbLine") (10 16348.3823529412
5712.6696832579 0.0) (11 16375.4524886878 5712.6696832579 0.0))
((0 . "LINE") (100 . "AcDbEntity") (8 . "LOUVERS") (62 . 7) (370 . 13) (100 . "AcDbLine") (10 16375.4524886878
5712.6696832579 0.0) (11 16442.3076923077 5712.6696832579 0.0))
((0 . "LINE") (100 . "AcDbEntity") (8 . "LOUVERS") (62 . 7) (370 . 13) (100 . "AcDbLine") (10 16442.3076923077
5712.6696832579 0.0) (11 16504.536199095 5712.6696832579 0.0))
((0 . "LINE") (100 . "AcDbEntity") (8 . "LOUVERS") (62 . 7) (370 . 13) (100 . "AcDbLine") (10 16504.536199095
5712.6696832579 0.0) (11 16540.9389140272 5712.6696832579 0.0))
((0 . "LINE") (100 . "AcDbEntity") (8 . "LOUVERS") (62 . 7) (370 . 13) (100 . "AcDbLine") (10 16540.9389140272
5712.6696832579 0.0) (11 16576.6742081448 5712.6696832579 0.0))
((0 . "LINE") (100 . "AcDbEntity") (8 . "LOUVERS") (62 . 7) (370 . 13) (100 . "AcDbLine") (10 16576.6742081448
5712.6696832579 0.0) (11 16625.5769230769 5712.6696832579 0.0))
((0 . "LINE") (100 . "AcDbEntity") (8 . "LOUVERS") (62 . 7) (370 . 13) (100 . "AcDbLine") (10 16625.5769230769
5712.6696832579 0.0) (11 16650.9389140271 5712.6696832579 0.0))
((0 . "LINE") (100 . "AcDbEntity") (8 . "LOUVERS") (62 . 7) (370 . 13) (100 . "AcDbLine") (10 16650.9389140271
5712.6696832579 0.0) (11 16696.1538461538 5712.6696832579 0.0))
((0 . "LINE") (100 . "AcDbEntity") (8 . "LOUVERS") (62 . 7) (370 . 13) (100 . "AcDbLine") (10 16696.1538461538
5712.6696832579 0.0) (11 16725.350678733 5712.6696832579 0.0))
((0 . "LINE") (100 . "AcDbEntity") (8 . "LOUVERS") (62 . 7) (370 . 13) (100 . "AcDbLine") (10 16725.350678733
5712.6696832579 0.0) (11 16773.7556561086 5712.6696832579 0.0))
((0 . "LINE") (100 . "AcDbEntity") (8 . "LOUVERS") (62 . 7) (370 . 13) (100 . "AcDbLine") (10 16773.7556561086
5712.6696832579 0.0) (11 16787.3303167421 5712.6696832579 0.0))
((0 . "LINE") (100 . "AcDbEntity") (8 . "LOUVERS") (62 . 7) (370 . 13) (100 . "AcDbLine") (10 16787.3303167421
5712.6696832579 0.0) (11 16787.3303167421 5610.8597285068 0.0))
((0 . "LINE") (100 . "AcDbEntity") (8 . "LOUVERS") (62 . 7) (370 . 13) (100 . "AcDbLine") (10 16787.3303167421
5610.8597285068 0.0) (11 16787.3303167421 3800.9049773756 0.0))
((0 . "LINE") (100 . "AcDbEntity") (8 . "LOUVERS") (62 . 7) (370 . 13) (100 . "AcDbLine") (10 16787.3303167421
3800.9049773756 0.0) (11 16773.7556561086 3800.9049773756 0.0))
((0 . "LINE") (100 . "AcDbEntity") (8 . "LOUVERS") (62 . 7) (370 . 13) (100 . "AcDbLine") (10 16773.7556561086
3800.9049773756 0.0) (11 16725.350678733 3800.9049773756 0.0))
((0 . "LINE") (100 . "AcDbEntity") (8 . "LOUVERS") (62 . 7) (370 . 13) (100 . "AcDbLine") (10 16725.350678733
3800.9049773756 0.0) (11 16696.1538461538 3800.9049773756 0.0))
((0 . "LINE") (100 . "AcDbEntity") (8 . "LOUVERS") (62 . 7) (370 . 13) (100 . "AcDbLine") (10 16696.1538461538
3800.9049773756 0.0) (11 16650.9389140271 3800.9049773756 0.0))
((0 . "LINE") (100 . "AcDbEntity") (8 . "LOUVERS") (62 . 7) (370 . 13) (100 . "AcDbLine") (10 16650.9389140271
3800.9049773756 0.0) (11 16625.5769230769 3800.9049773756 0.0))
((0 . "LINE") (100 . "AcDbEntity") (8 . "LOUVERS") (62 . 7) (370 . 13) (100 . "AcDbLine") (10 16625.5769230769
3800.9049773756 0.0) (11 16576.6742081448 3800.9049773756 0.0))
((0 . "LINE") (100 . "AcDbEntity") (8 . "LOUVERS") (62 . 7) (370 . 13) (100 . "AcDbLine") (10 16576.6742081448
3800.9049773756 0.0) (11 16540.9389140272 3800.9049773756 0.0))
((0 . "LINE") (100 . "AcDbEntity") (8 . "LOUVERS") (62 . 7) (370 . 13) (100 . "AcDbLine") (10 16540.9389140272
3800.9049773756 0.0) (11 16504.536199095 3800.9049773756 0.0))
((0 . "LINE") (100 . "AcDbEntity") (8 . "LOUVERS") (62 . 7) (370 . 13) (100 . "AcDbLine") (10 16504.536199095
3800.9049773756 0.0) (11 16442.3076923077 3800.9049773756 0.0))
((0 . "LINE") (100 . "AcDbEntity") (8 . "LOUVERS") (62 . 7) (370 . 13) (100 . "AcDbLine") (10 16442.3076923077
3800.9049773756 0.0) (11 16375.4524886878 3800.9049773756 0.0))
((0 . "LINE") (100 . "AcDbEntity") (8 . "LOUVERS") (62 . 7) (370 . 13) (100 . "AcDbLine") (10 16375.4524886878
3800.9049773756 0.0) (11 16348.3823529412 3800.9049773756 0.0))
((0 . "LINE") (100 . "AcDbEntity") (8 . "LOUVERS") (62 . 7) (370 . 13) (100 . "AcDbLine") (10 16348.3823529412
3800.9049773756 0.0) (11 16301.6063348416 3800.9049773756 0.0))
((0 . "LINE") (100 . "AcDbEntity") (8 . "LOUVERS") (62 . 7) (370 . 13) (100 . "AcDbLine") (10 16301.6063348416
3800.9049773756 0.0) (11 16274.2986425339 3800.9049773756 0.0))
((0 . "LINE") (100 . "AcDbEntity") (8 . "LOUVERS") (62 . 7) (370 . 13) (100 . "AcDbLine") (10 16274.2986425339
3800.9049773756 0.0) (11 16221.7194570136 3800.9049773756 0.0))
((0 . "LINE") (100 . "AcDbEntity") (8 . "LOUVERS") (62 . 7) (370 . 13) (100 . "AcDbLine") (10 16221.7194570136
3800.9049773756 0.0) (11 16221.7194570136 5610.8597285068 0.0))
((0 . "LINE") (100 . "AcDbEntity") (8 . "LOUVERS") (62 . 7) (370 . 13) (100 . "AcDbLine") (10 16221.7194570136
5610.8597285068 0.0) (11 16221.7194570136 5712.6696832579 0.0))
((0 . "LINE") (100 . "AcDbEntity") (8 . "LOUVERS") (62 . 7) (370 . 13) (100 . "AcDbLine") (10 16274.2986425339
5712.6696832579 0.0) (11 16274.2986425339 5610.8597285068 0.0))
((0 . "LINE") (100 . "AcDbEntity") (8 . "LOUVERS") (62 . 7) (370 . 13) (100 . "AcDbLine") (10 16274.2986425339
5610.8597285068 0.0) (11 16274.2986425339 3800.9049773756 0.0))
((0 . "LINE") (100 . "AcDbEntity") (8 . "LOUVERS") (62 . 7) (370 . 13) (100 . "AcDbLine") (10 16301.6063348416
5712.6696832579 0.0) (11 16301.6063348416 5610.8597285068 0.0))
((0 . "LINE") (100 . "AcDbEntity") (8 . "LOUVERS") (62 . 7) (370 . 13) (100 . "AcDbLine") (10 16301.6063348416
5610.8597285068 0.0) (11 16301.6063348416 3800.9049773756 0.0))
((0 . "LINE") (100 . "AcDbEntity") (8 . "LOUVERS") (62 . 7) (370 . 13) (100 . "AcDbLine") (10 16348.3823529412
5712.6696832579 0.0) (11 16348.3823529412 5610.8597285068 0.0))
((0 . "LINE") (100 . "AcDbEntity") (8 . "LOUVERS") (62 . 7) (370 . 13) (100 . "AcDbLine") (10 16348.3823529412
5610.8597285068 0.0) (11 16348.3823529412 3800.9049773756 0.0))
((0 . "LINE") (100 . "AcDbEntity") (8 . "LOUVERS") (62 . 7) (370 . 13) (100 . "AcDbLine") (10 16375.4524886878
5712.6696832579 0.0) (11 16375.4524886878 5610.8597285068 0.0))
((0 . "LINE") (100 . "AcDbEntity") (8 . "LOUVERS") (62 . 7) (370 . 13) (100 . "AcDbLine") (10 16375.4524886878
5610.8597285068 0.0) (11 16375.4524886878 3800.9049773756 0.0))
((0 . "LINE") (100 . "AcDbEntity") (8 . "LOUVERS") (62 . 7) (370 . 13) (100 . "AcDbLine") (10 16442.3076923077
5712.6696832579 0.0) (11 16442.3076923077 5610.8597285068 0.0))
((0 . "LINE") (100 . "AcDbEntity") (8 . "LOUVERS") (62 . 7) (370 . 13) (100 . "AcDbLine") (10 16442.3076923077
5610.8597285068 0.0) (11 16442.3076923077 3800.9049773756 0.0))
((0 . "LINE") (100 . "AcDbEntity") (8 . "LOUVERS") (62 . 7) (370 . 13) (100 . "AcDbLine") (10 16504.536199095
5712.6696832579 0.0) (11 16504.536199095 5610.8597285068 0.0))
((0 . "LINE") (100 . "AcDbEntity") (8 . "LOUVERS") (62 . 7) (370 . 13) (100 . "AcDbLine") (10 16504.536199095
5610.8597285068 0.0) (11 16504.536199095 3800.9049773756 0.0))
((0 . "LINE") (100 . "AcDbEntity") (8 . "LOUVERS") (62 . 7) (370 . 13) (100 . "AcDbLine") (10 16540.9389140272
5712.6696832579 0.0) (11 16540.9389140272 5610.8597285068 0.0))
((0 . "LINE") (100 . "AcDbEntity") (8 . "LOUVERS") (62 . 7) (370 . 13) (100 . "AcDbLine") (10 16540.9389140272
5610.8597285068 0.0) (11 16540.9389140272 3800.9049773756 0.0))
((0 . "LINE") (100 . "AcDbEntity") (8 . "LOUVERS") (62 . 7) (370 . 13) (100 . "AcDbLine") (10 16576.6742081448
5712.6696832579 0.0) (11 16576.6742081448 5610.8597285068 0.0))
((0 . "LINE") (100 . "AcDbEntity") (8 . "LOUVERS") (62 . 7) (370 . 13) (100 . "AcDbLine") (10 16576.6742081448
5610.8597285068 0.0) (11 16576.6742081448 3800.9049773756 0.0))
((0 . "LINE") (100 . "AcDbEntity") (8 . "LOUVERS") (62 . 7) (370 . 13) (100 . "AcDbLine") (10 16625.5769230769
5712.6696832579 0.0) (11 16625.5769230769 5610.8597285068 0.0))
((0 . "LINE") (100 . "AcDbEntity") (8 . "LOUVERS") (62 . 7) (370 . 13) (100 . "AcDbLine") (10 16625.5769230769
5610.8597285068 0.0) (11 16625.5769230769 3800.9049773756 0.0))
((0 . "LINE") (100 . "AcDbEntity") (8 . "LOUVERS") (62 . 7) (370 . 13) (100 . "AcDbLine") (10 16650.9389140271
5712.6696832579 0.0) (11 16650.9389140271 5610.8597285068 0.0))
((0 . "LINE") (100 . "AcDbEntity") (8 . "LOUVERS") (62 . 7) (370 . 13) (100 . "AcDbLine") (10 16650.9389140271
5610.8597285068 0.0) (11 16650.9389140271 3800.9049773756 0.0))
((0 . "LINE") (100 . "AcDbEntity") (8 . "LOUVERS") (62 . 7) (370 . 13) (100 . "AcDbLine") (10 16696.1538461538
5712.6696832579 0.0) (11 16696.1538461538 5610.8597285068 0.0))
((0 . "LINE") (100 . "AcDbEntity") (8 . "LOUVERS") (62 . 7) (370 . 13) (100 . "AcDbLine") (10 16696.1538461538
5610.8597285068 0.0) (11 16696.1538461538 3800.9049773756 0.0))
((0 . "LINE") (100 . "AcDbEntity") (8 . "LOUVERS") (62 . 7) (370 . 13) (100 . "AcDbLine") (10 16725.350678733
5712.6696832579 0.0) (11 16725.350678733 5610.8597285068 0.0))
((0 . "LINE") (100 . "AcDbEntity") (8 . "LOUVERS") (62 . 7) (370 . 13) (100 . "AcDbLine") (10 16725.350678733
5610.8597285068 0.0) (11 16725.350678733 3800.9049773756 0.0))
((0 . "LINE") (100 . "AcDbEntity") (8 . "LOUVERS") (62 . 7) (370 . 13) (100 . "AcDbLine") (10 16773.7556561086
5712.6696832579 0.0) (11 16773.7556561086 5610.8597285068 0.0))
((0 . "LINE") (100 . "AcDbEntity") (8 . "LOUVERS") (62 . 7) (370 . 13) (100 . "AcDbLine") (10 16773.7556561086
5610.8597285068 0.0) (11 16773.7556561086 3800.9049773756 0.0))
((0 . "LINE") (100 . "AcDbEntity") (8 . "LOUVERS") (62 . 7) (370 . 13) (100 . "AcDbLine") (10 13212.6696832579
3212.6696832579 0.0) (11 13246.8778280543 3212.6696832579 0.0))
((0 . "LINE") (100 . "AcDbEntity") (8 . "LOUVERS") (62 . 7) (370 . 13) (100 . "AcDbLine") (10 13246.8778280543
3212.6696832579 0.0) (11 13296.2895927602 3212.6696832579 0.0))
((0 . "LINE") (100 . "AcDbEntity") (8 . "LOUVERS") (62 . 7) (370 . 13) (100 . "AcDbLine") (10 13296.2895927602
3212.6696832579 0.0) (11 13333.257918552 3212.6696832579 0.0))
((0 . "LINE") (100 . "AcDbEntity") (8 . "LOUVERS") (62 . 7) (370 . 13) (100 . "AcDbLine") (10 13333.257918552
3212.6696832579 0.0) (11 13379.1628959276 3212.6696832579 0.0))
((0 . "LINE") (100 . "AcDbEntity") (8 . "LOUVERS") (62 . 7) (370 . 13) (100 . "AcDbLine") (10 13379.1628959276
3212.6696832579 0.0) (11 13416.2895927602 3212.6696832579 0.0))
((0 . "LINE") (100 . "AcDbEntity") (8 . "LOUVERS") (62 . 7) (370 . 13) (100 . "AcDbLine") (10 13416.2895927602
3212.6696832579 0.0) (11 13451.7307692308 3212.6696832579 0.0))
((0 . "LINE") (100 . "AcDbEntity") (8 . "LOUVERS") (62 . 7) (370 . 13) (100 . "AcDbLine") (10 13451.7307692308
3212.6696832579 0.0) (11 13498.2918552036 3212.6696832579 0.0))
((0 . "LINE") (100 . "AcDbEntity") (8 . "LOUVERS") (62 . 7) (370 . 13) (100 . "AcDbLine") (10 13498.2918552036
3212.6696832579 0.0) (11 13531.221719457 3212.6696832579 0.0))
((0 . "LINE") (100 . "AcDbEntity") (8 . "LOUVERS") (62 . 7) (370 . 13) (100 . "AcDbLine") (10 13531.221719457
3212.6696832579 0.0) (11 13570.4411764706 3212.6696832579 0.0))
((0 . "LINE") (100 . "AcDbEntity") (8 . "LOUVERS") (62 . 7) (370 . 13) (100 . "AcDbLine") (10 13570.4411764706
3212.6696832579 0.0) (11 13600.3959276018 3212.6696832579 0.0))
((0 . "LINE") (100 . "AcDbEntity") (8 . "LOUVERS") (62 . 7) (370 . 13) (100 . "AcDbLine") (10 13600.3959276018
3212.6696832579 0.0) (11 13641.4479638009 3212.6696832579 0.0))
((0 . "LINE") (100 . "AcDbEntity") (8 . "LOUVERS") (62 . 7) (370 . 13) (100 . "AcDbLine") (10 13641.4479638009
3212.6696832579 0.0) (11 13679.6832579186 3212.6696832579 0.0))
((0 . "LINE") (100 . "AcDbEntity") (8 . "LOUVERS") (62 . 7) (370 . 13) (100 . "AcDbLine") (10 13679.6832579186
3212.6696832579 0.0) (11 13722.0814479638 3212.6696832579 0.0))
((0 . "LINE") (100 . "AcDbEntity") (8 . "LOUVERS") (62 . 7) (370 . 13) (100 . "AcDbLine") (10 13722.0814479638
3212.6696832579 0.0) (11 13757.5113122172 3212.6696832579 0.0))
((0 . "LINE") (100 . "AcDbEntity") (8 . "LOUVERS") (62 . 7) (370 . 13) (100 . "AcDbLine") (10 13757.5113122172
3212.6696832579 0.0) (11 13791.9117647059 3212.6696832579 0.0))
((0 . "LINE") (100 . "AcDbEntity") (8 . "LOUVERS") (62 . 7) (370 . 13) (100 . "AcDbLine") (10 13791.9117647059
3212.6696832579 0.0) (11 13824.4796380091 3212.6696832579 0.0))
((0 . "LINE") (100 . "AcDbEntity") (8 . "LOUVERS") (62 . 7) (370 . 13) (100 . "AcDbLine") (10 13824.4796380091
3212.6696832579 0.0) (11 13857.6583710407 3212.6696832579 0.0))
((0 . "LINE") (100 . "AcDbEntity") (8 . "LOUVERS") (62 . 7) (370 . 13) (100 . "AcDbLine") (10 13857.6583710407
3212.6696832579 0.0) (11 13887.5791855204 3212.6696832579 0.0))
((0 . "LINE") (100 . "AcDbEntity") (8 . "LOUVERS") (62 . 7) (370 . 13) (100 . "AcDbLine") (10 13887.5791855204
3212.6696832579 0.0) (11 13923.5520361991 3212.6696832579 0.0))
((0 . "LINE") (100 . "AcDbEntity") (8 . "LOUVERS") (62 . 7) (370 . 13) (100 . "AcDbLine") (10 13923.5520361991
3212.6696832579 0.0) (11 13954.7850678733 3212.6696832579 0.0))
((0 . "LINE") (100 . "AcDbEntity") (8 . "LOUVERS") (62 . 7) (370 . 13) (100 . "AcDbLine") (10 13954.7850678733
3212.6696832579 0.0) (11 13991.7081447964 3212.6696832579 0.0))
((0 . "LINE") (100 . "AcDbEntity") (8 . "LOUVERS") (62 . 7) (370 . 13) (100 . "AcDbLine") (10 13991.7081447964
3212.6696832579 0.0) (11 14027.9298642534 3212.6696832579 0.0))
((0 . "LINE") (100 . "AcDbEntity") (8 . "LOUVERS") (62 . 7) (370 . 13) (100 . "AcDbLine") (10 14027.9298642534
3212.6696832579 0.0) (11 14082.8846153846 3212.6696832579 0.0))
((0 . "LINE") (100 . "AcDbEntity") (8 . "LOUVERS") (62 . 7) (370 . 13) (100 . "AcDbLine") (10 14082.8846153846
3212.6696832579 0.0) (11 14109.8190045249 3212.6696832579 0.0))
((0 . "LINE") (100 . "AcDbEntity") (8 . "LOUVERS") (62 . 7) (370 . 13) (100 . "AcDbLine") (10 14109.8190045249
3212.6696832579 0.0) (11 14142.7036199095 3212.6696832579 0.0))
((0 . "LINE") (100 . "AcDbEntity") (8 . "LOUVERS") (62 . 7) (370 . 13) (100 . "AcDbLine") (10 14142.7036199095
3212.6696832579 0.0) (11 14171.6968325792 3212.6696832579 0.0))
((0 . "LINE") (100 . "AcDbEntity") (8 . "LOUVERS") (62 . 7) (370 . 13) (100 . "AcDbLine") (10 14171.6968325792
3212.6696832579 0.0) (11 14209.5248868778 3212.6696832579 0.0))
((0 . "LINE") (100 . "AcDbEntity") (8 . "LOUVERS") (62 . 7) (370 . 13) (100 . "AcDbLine") (10 14209.5248868778
3212.6696832579 0.0) (11 14231.8552036199 3212.6696832579 0.0))
((0 . "LINE") (100 . "AcDbEntity") (8 . "LOUVERS") (62 . 7) (370 . 13) (100 . "AcDbLine") (10 14231.8552036199
3212.6696832579 0.0) (11 14279.1742081448 3212.6696832579 0.0))
((0 . "LINE") (100 . "AcDbEntity") (8 . "LOUVERS") (62 . 7) (370 . 13) (100 . "AcDbLine") (10 14279.1742081448
3212.6696832579 0.0) (11 14308.834841629 3212.6696832579 0.0))
((0 . "LINE") (100 . "AcDbEntity") (8 . "LOUVERS") (62 . 7) (370 . 13) (100 . "AcDbLine") (10 14308.834841629
3212.6696832579 0.0) (11 14347.5904977376 3212.6696832579 0.0))
((0 . "LINE") (100 . "AcDbEntity") (8 . "LOUVERS") (62 . 7) (370 . 13) (100 . "AcDbLine") (10 14347.5904977376
3212.6696832579 0.0) (11 14391.4366515837 3212.6696832579 0.0))
((0 . "LINE") (100 . "AcDbEntity") (8 . "LOUVERS") (62 . 7) (370 . 13) (100 . "AcDbLine") (10 14391.4366515837
3212.6696832579 0.0) (11 14408.2239819005 3212.6696832579 0.0))
((0 . "LINE") (100 . "AcDbEntity") (8 . "LOUVERS") (62 . 7) (370 . 13) (100 . "AcDbLine") (10 14408.2239819005
3212.6696832579 0.0) (11 14446.9343891403 3212.6696832579 0.0))
((0 . "LINE") (100 . "AcDbEntity") (8 . "LOUVERS") (62 . 7) (370 . 13) (100 . "AcDbLine") (10 14446.9343891403
3212.6696832579 0.0) (11 14466.5045248869 3212.6696832579 0.0))
((0 . "LINE") (100 . "AcDbEntity") (8 . "LOUVERS") (62 . 7) (370 . 13) (100 . "AcDbLine") (10 14466.5045248869
3212.6696832579 0.0) (11 14506.2443438914 3212.6696832579 0.0))
((0 . "LINE") (100 . "AcDbEntity") (8 . "LOUVERS") (62 . 7) (370 . 13) (100 . "AcDbLine") (10 14506.2443438914
3212.6696832579 0.0) (11 14522.2058823529 3212.6696832579 0.0))
((0 . "LINE") (100 . "AcDbEntity") (8 . "LOUVERS") (62 . 7) (370 . 13) (100 . "AcDbLine") (10 14522.2058823529
3212.6696832579 0.0) (11 14569.1742081448 3212.6696832579 0.0))
((0 . "LINE") (100 . "AcDbEntity") (8 . "LOUVERS") (62 . 7) (370 . 13) (100 . "AcDbLine") (10 14569.1742081448
3212.6696832579 0.0) (11 14608.0316742081 3212.6696832579 0.0))
((0 . "LINE") (100 . "AcDbEntity") (8 . "LOUVERS") (62 . 7) (370 . 13) (100 . "AcDbLine") (10 14608.0316742081
3212.6696832579 0.0) (11 14622.3416289593 3212.6696832579 0.0))
((0 . "LINE") (100 . "AcDbEntity") (8 . "LOUVERS") (62 . 7) (370 . 13) (100 . "AcDbLine") (10 14622.3416289593
3212.6696832579 0.0) (11 14658.3936651584 3212.6696832579 0.0))
((0 . "LINE") (100 . "AcDbEntity") (8 . "LOUVERS") (62 . 7) (370 . 13) (100 . "AcDbLine") (10 14658.3936651584
3212.6696832579 0.0) (11 14687.5113122172 3212.6696832579 0.0))
((0 . "LINE") (100 . "AcDbEntity") (8 . "LOUVERS") (62 . 7) (370 . 13) (100 . "AcDbLine") (10 14687.5113122172
3212.6696832579 0.0) (11 14734.3552036199 3212.6696832579 0.0))
((0 . "LINE") (100 . "AcDbEntity") (8 . "LOUVERS") (62 . 7) (370 . 13) (100 . "AcDbLine") (10 14734.3552036199
3212.6696832579 0.0) (11 14774.5475113122 3212.6696832579 0.0))
((0 . "LINE") (100 . "AcDbEntity") (8 . "LOUVERS") (62 . 7) (370 . 13) (100 . "AcDbLine") (10 14774.5475113122
3212.6696832579 0.0) (11 14802.0475113122 3212.6696832579 0.0))
((0 . "LINE") (100 . "AcDbEntity") (8 . "LOUVERS") (62 . 7) (370 . 13) (100 . "AcDbLine") (10 14802.0475113122
3212.6696832579 0.0) (11 14829.8755656109 3212.6696832579 0.0))
((0 . "LINE") (100 . "AcDbEntity") (8 . "LOUVERS") (62 . 7) (370 . 13) (100 . "AcDbLine") (10 14829.8755656109
3212.6696832579 0.0) (11 14864.8303167421 3212.6696832579 0.0))
((0 . "LINE") (100 . "AcDbEntity") (8 . "LOUVERS") (62 . 7) (370 . 13) (100 . "AcDbLine") (10 14864.8303167421
3212.6696832579 0.0) (11 14935.5090497738 3212.6696832579 0.0))
((0 . "LINE") (100 . "AcDbEntity") (8 . "LOUVERS") (62 . 7) (370 . 13) (100 . "AcDbLine") (10 14935.5090497738
3212.6696832579 0.0) (11 14997.9751131222 3212.6696832579 0.0))
((0 . "LINE") (100 . "AcDbEntity") (8 . "LOUVERS") (62 . 7) (370 . 13) (100 . "AcDbLine") (10 14997.9751131222
3212.6696832579 0.0) (11 15031.9004524887 3212.6696832579 0.0))
((0 . "LINE") (100 . "AcDbEntity") (8 . "LOUVERS") (62 . 7) (370 . 13) (100 . "AcDbLine") (10 15031.9004524887
3212.6696832579 0.0) (11 15067.2963800905 3212.6696832579 0.0))
((0 . "LINE") (100 . "AcDbEntity") (8 . "LOUVERS") (62 . 7) (370 . 13) (100 . "AcDbLine") (10 15067.2963800905
3212.6696832579 0.0) (11 15102.6244343891 3212.6696832579 0.0))
((0 . "LINE") (100 . "AcDbEntity") (8 . "LOUVERS") (62 . 7) (370 . 13) (100 . "AcDbLine") (10 15102.6244343891
3212.6696832579 0.0) (11 15143.0995475113 3212.6696832579 0.0))
((0 . "LINE") (100 . "AcDbEntity") (8 . "LOUVERS") (62 . 7) (370 . 13) (100 . "AcDbLine") (10 15143.0995475113
3212.6696832579 0.0) (11 15178.778280543 3212.6696832579 0.0))
((0 . "LINE") (100 . "AcDbEntity") (8 . "LOUVERS") (62 . 7) (370 . 13) (100 . "AcDbLine") (10 15178.778280543
3212.6696832579 0.0) (11 15215.8257918552 3212.6696832579 0.0))
((0 . "LINE") (100 . "AcDbEntity") (8 . "LOUVERS") (62 . 7) (370 . 13) (100 . "AcDbLine") (10 15215.8257918552
3212.6696832579 0.0) (11 15251.1085972851 3212.6696832579 0.0))
((0 . "LINE") (100 . "AcDbEntity") (8 . "LOUVERS") (62 . 7) (370 . 13) (100 . "AcDbLine") (10 15251.1085972851
3212.6696832579 0.0) (11 15287.8280542986 3212.6696832579 0.0))
((0 . "LINE") (100 . "AcDbEntity") (8 . "LOUVERS") (62 . 7) (370 . 13) (100 . "AcDbLine") (10 15287.8280542986
3212.6696832579 0.0) (11 15325.3846153846 3212.6696832579 0.0))
((0 . "LINE") (100 . "AcDbEntity") (8 . "LOUVERS") (62 . 7) (370 . 13) (100 . "AcDbLine") (10 15325.3846153846
3212.6696832579 0.0) (11 15360.9841628959 3212.6696832579 0.0))
((0 . "LINE") (100 . "AcDbEntity") (8 . "LOUVERS") (62 . 7) (370 . 13) (100 . "AcDbLine") (10 15360.9841628959
3212.6696832579 0.0) (11 15395.5429864253 3212.6696832579 0.0))
((0 . "LINE") (100 . "AcDbEntity") (8 . "LOUVERS") (62 . 7) (370 . 13) (100 . "AcDbLine") (10 15395.5429864253
3212.6696832579 0.0) (11 15430.7466063348 3212.6696832579 0.0))
((0 . "LINE") (100 . "AcDbEntity") (8 . "LOUVERS") (62 . 7) (370 . 13) (100 . "AcDbLine") (10 15430.7466063348
3212.6696832579 0.0) (11 15463.2352941176 3212.6696832579 0.0))
((0 . "LINE") (100 . "AcDbEntity") (8 . "LOUVERS") (62 . 7) (370 . 13) (100 . "AcDbLine") (10 15463.2352941176
3212.6696832579 0.0) (11 15509.4343891403 3212.6696832579 0.0))
((0 . "LINE") (100 . "AcDbEntity") (8 . "LOUVERS") (62 . 7) (370 . 13) (100 . "AcDbLine") (10 15509.4343891403
3212.6696832579 0.0) (11 15541.4819004525 3212.6696832579 0.0))
((0 . "LINE") (100 . "AcDbEntity") (8 . "LOUVERS") (62 . 7) (370 . 13) (100 . "AcDbLine") (10 15541.4819004525
3212.6696832579 0.0) (11 15579.1176470588 3212.6696832579 0.0))
((0 . "LINE") (100 . "AcDbEntity") (8 . "LOUVERS") (62 . 7) (370 . 13) (100 . "AcDbLine") (10 15579.1176470588
3212.6696832579 0.0) (11 15612.036199095 3212.6696832579 0.0))
((0 . "LINE") (100 . "AcDbEntity") (8 . "LOUVERS") (62 . 7) (370 . 13) (100 . "AcDbLine") (10 15612.036199095
3212.6696832579 0.0) (11 15644.6606334842 3212.6696832579 0.0))
((0 . "LINE") (100 . "AcDbEntity") (8 . "LOUVERS") (62 . 7) (370 . 13) (100 . "AcDbLine") (10 15644.6606334842
3212.6696832579 0.0) (11 15681.0180995475 3212.6696832579 0.0))
((0 . "LINE") (100 . "AcDbEntity") (8 . "LOUVERS") (62 . 7) (370 . 13) (100 . "AcDbLine") (10 15681.0180995475
3212.6696832579 0.0) (11 15698.7895927602 3212.6696832579 0.0))
((0 . "LINE") (100 . "AcDbEntity") (8 . "LOUVERS") (62 . 7) (370 . 13) (100 . "AcDbLine") (10 15698.7895927602
3212.6696832579 0.0) (11 15738.0542986425 3212.6696832579 0.0))
((0 . "LINE") (100 . "AcDbEntity") (8 . "LOUVERS") (62 . 7) (370 . 13) (100 . "AcDbLine") (10 15738.0542986425
3212.6696832579 0.0) (11 15756.8552036199 3212.6696832579 0.0))
((0 . "LINE") (100 . "AcDbEntity") (8 . "LOUVERS") (62 . 7) (370 . 13) (100 . "AcDbLine") (10 15756.8552036199
3212.6696832579 0.0) (11 15802.963800905 3212.6696832579 0.0))
((0 . "LINE") (100 . "AcDbEntity") (8 . "LOUVERS") (62 . 7) (370 . 13) (100 . "AcDbLine") (10 15802.963800905
3212.6696832579 0.0) (11 15828.6312217195 3212.6696832579 0.0))
((0 . "LINE") (100 . "AcDbEntity") (8 . "LOUVERS") (62 . 7) (370 . 13) (100 . "AcDbLine") (10 15828.6312217195
3212.6696832579 0.0) (11 15872.0814479638 3212.6696832579 0.0))
((0 . "LINE") (100 . "AcDbEntity") (8 . "LOUVERS") (62 . 7) (370 . 13) (100 . "AcDbLine") (10 15872.0814479638
3212.6696832579 0.0) (11 15901.0633484163 3212.6696832579 0.0))
((0 . "LINE") (100 . "AcDbEntity") (8 . "LOUVERS") (62 . 7) (370 . 13) (100 . "AcDbLine") (10 15901.0633484163
3212.6696832579 0.0) (11 15916.2895927602 3212.6696832579 0.0))
((0 . "LINE") (100 . "AcDbEntity") (8 . "LOUVERS") (62 . 7) (370 . 13) (100 . "AcDbLine") (10 15916.2895927602
3212.6696832579 0.0) (11 15916.2895927602 2952.4886877828 0.0))
((0 . "LINE") (100 . "AcDbEntity") (8 . "LOUVERS") (62 . 7) (370 . 13) (100 . "AcDbLine") (10 15916.2895927602
2952.4886877828 0.0) (11 15901.0633484163 2952.4886877828 0.0))
((0 . "LINE") (100 . "AcDbEntity") (8 . "LOUVERS") (62 . 7) (370 . 13) (100 . "AcDbLine") (10 15901.0633484163
2952.4886877828 0.0) (11 15872.0814479638 2952.4886877828 0.0))
((0 . "LINE") (100 . "AcDbEntity") (8 . "LOUVERS") (62 . 7) (370 . 13) (100 . "AcDbLine") (10 15872.0814479638
2952.4886877828 0.0) (11 15828.6312217195 2952.4886877828 0.0))
((0 . "LINE") (100 . "AcDbEntity") (8 . "LOUVERS") (62 . 7) (370 . 13) (100 . "AcDbLine") (10 15828.6312217195
2952.4886877828 0.0) (11 15802.963800905 2952.4886877828 0.0))
((0 . "LINE") (100 . "AcDbEntity") (8 . "LOUVERS") (62 . 7) (370 . 13) (100 . "AcDbLine") (10 15802.963800905
2952.4886877828 0.0) (11 15756.8552036199 2952.4886877828 0.0))
((0 . "LINE") (100 . "AcDbEntity") (8 . "LOUVERS") (62 . 7) (370 . 13) (100 . "AcDbLine") (10 15756.8552036199
2952.4886877828 0.0) (11 15738.0542986425 2952.4886877828 0.0))
((0 . "LINE") (100 . "AcDbEntity") (8 . "LOUVERS") (62 . 7) (370 . 13) (100 . "AcDbLine") (10 15738.0542986425
2952.4886877828 0.0) (11 15698.7895927602 2952.4886877828 0.0))
((0 . "LINE") (100 . "AcDbEntity") (8 . "LOUVERS") (62 . 7) (370 . 13) (100 . "AcDbLine") (10 15698.7895927602
2952.4886877828 0.0) (11 15681.0180995475 2952.4886877828 0.0))
((0 . "LINE") (100 . "AcDbEntity") (8 . "LOUVERS") (62 . 7) (370 . 13) (100 . "AcDbLine") (10 15681.0180995475
2952.4886877828 0.0) (11 15644.6606334842 2952.4886877828 0.0))
((0 . "LINE") (100 . "AcDbEntity") (8 . "LOUVERS") (62 . 7) (370 . 13) (100 . "AcDbLine") (10 15644.6606334842
2952.4886877828 0.0) (11 15612.036199095 2952.4886877828 0.0))
((0 . "LINE") (100 . "AcDbEntity") (8 . "LOUVERS") (62 . 7) (370 . 13) (100 . "AcDbLine") (10 15612.036199095
2952.4886877828 0.0) (11 15579.1176470588 2952.4886877828 0.0))
((0 . "LINE") (100 . "AcDbEntity") (8 . "LOUVERS") (62 . 7) (370 . 13) (100 . "AcDbLine") (10 15579.1176470588
2952.4886877828 0.0) (11 15541.4819004525 2952.4886877828 0.0))
((0 . "LINE") (100 . "AcDbEntity") (8 . "LOUVERS") (62 . 7) (370 . 13) (100 . "AcDbLine") (10 15541.4819004525
2952.4886877828 0.0) (11 15509.4343891403 2952.4886877828 0.0))
((0 . "LINE") (100 . "AcDbEntity") (8 . "LOUVERS") (62 . 7) (370 . 13) (100 . "AcDbLine") (10 15509.4343891403
2952.4886877828 0.0) (11 15463.2352941176 2952.4886877828 0.0))
((0 . "LINE") (100 . "AcDbEntity") (8 . "LOUVERS") (62 . 7) (370 . 13) (100 . "AcDbLine") (10 15463.2352941176
2952.4886877828 0.0) (11 15430.7466063348 2952.4886877828 0.0))
((0 . "LINE") (100 . "AcDbEntity") (8 . "LOUVERS") (62 . 7) (370 . 13) (100 . "AcDbLine") (10 15430.7466063348
2952.4886877828 0.0) (11 15395.5429864253 2952.4886877828 0.0))
((0 . "LINE") (100 . "AcDbEntity") (8 . "LOUVERS") (62 . 7) (370 . 13) (100 . "AcDbLine") (10 15395.5429864253
2952.4886877828 0.0) (11 15360.9841628959 2952.4886877828 0.0))
((0 . "LINE") (100 . "AcDbEntity") (8 . "LOUVERS") (62 . 7) (370 . 13) (100 . "AcDbLine") (10 15360.9841628959
2952.4886877828 0.0) (11 15325.3846153846 2952.4886877828 0.0))
((0 . "LINE") (100 . "AcDbEntity") (8 . "LOUVERS") (62 . 7) (370 . 13) (100 . "AcDbLine") (10 15325.3846153846
2952.4886877828 0.0) (11 15287.8280542986 2952.4886877828 0.0))
((0 . "LINE") (100 . "AcDbEntity") (8 . "LOUVERS") (62 . 7) (370 . 13) (100 . "AcDbLine") (10 15287.8280542986
2952.4886877828 0.0) (11 15251.1085972851 2952.4886877828 0.0))
((0 . "LINE") (100 . "AcDbEntity") (8 . "LOUVERS") (62 . 7) (370 . 13) (100 . "AcDbLine") (10 15251.1085972851
2952.4886877828 0.0) (11 15215.8257918552 2952.4886877828 0.0))
((0 . "LINE") (100 . "AcDbEntity") (8 . "LOUVERS") (62 . 7) (370 . 13) (100 . "AcDbLine") (10 15215.8257918552
2952.4886877828 0.0) (11 15178.778280543 2952.4886877828 0.0))
((0 . "LINE") (100 . "AcDbEntity") (8 . "LOUVERS") (62 . 7) (370 . 13) (100 . "AcDbLine") (10 15178.778280543
2952.4886877828 0.0) (11 15143.0995475113 2952.4886877828 0.0))
((0 . "LINE") (100 . "AcDbEntity") (8 . "LOUVERS") (62 . 7) (370 . 13) (100 . "AcDbLine") (10 15143.0995475113
2952.4886877828 0.0) (11 15102.6244343891 2952.4886877828 0.0))
((0 . "LINE") (100 . "AcDbEntity") (8 . "LOUVERS") (62 . 7) (370 . 13) (100 . "AcDbLine") (10 15102.6244343891
2952.4886877828 0.0) (11 15067.2963800905 2952.4886877828 0.0))
((0 . "LINE") (100 . "AcDbEntity") (8 . "LOUVERS") (62 . 7) (370 . 13) (100 . "AcDbLine") (10 15067.2963800905
2952.4886877828 0.0) (11 15031.9004524887 2952.4886877828 0.0))
((0 . "LINE") (100 . "AcDbEntity") (8 . "LOUVERS") (62 . 7) (370 . 13) (100 . "AcDbLine") (10 15031.9004524887
2952.4886877828 0.0) (11 14997.9751131222 2952.4886877828 0.0))
((0 . "LINE") (100 . "AcDbEntity") (8 . "LOUVERS") (62 . 7) (370 . 13) (100 . "AcDbLine") (10 14997.9751131222
2952.4886877828 0.0) (11 14935.5090497738 2952.4886877828 0.0))
((0 . "LINE") (100 . "AcDbEntity") (8 . "LOUVERS") (62 . 7) (370 . 13) (100 . "AcDbLine") (10 14935.5090497738
2952.4886877828 0.0) (11 14864.8303167421 2952.4886877828 0.0))
((0 . "LINE") (100 . "AcDbEntity") (8 . "LOUVERS") (62 . 7) (370 . 13) (100 . "AcDbLine") (10 14864.8303167421
2952.4886877828 0.0) (11 14829.8755656109 2952.4886877828 0.0))
((0 . "LINE") (100 . "AcDbEntity") (8 . "LOUVERS") (62 . 7) (370 . 13) (100 . "AcDbLine") (10 14829.8755656109
2952.4886877828 0.0) (11 14802.0475113122 2952.4886877828 0.0))
((0 . "LINE") (100 . "AcDbEntity") (8 . "LOUVERS") (62 . 7) (370 . 13) (100 . "AcDbLine") (10 14802.0475113122
2952.4886877828 0.0) (11 14774.5475113122 2952.4886877828 0.0))
((0 . "LINE") (100 . "AcDbEntity") (8 . "LOUVERS") (62 . 7) (370 . 13) (100 . "AcDbLine") (10 14774.5475113122
2952.4886877828 0.0) (11 14734.3552036199 2952.4886877828 0.0))
((0 . "LINE") (100 . "AcDbEntity") (8 . "LOUVERS") (62 . 7) (370 . 13) (100 . "AcDbLine") (10 14734.3552036199
2952.4886877828 0.0) (11 14687.5113122172 2952.4886877828 0.0))
((0 . "LINE") (100 . "AcDbEntity") (8 . "LOUVERS") (62 . 7) (370 . 13) (100 . "AcDbLine") (10 14687.5113122172
2952.4886877828 0.0) (11 14658.3936651584 2952.4886877828 0.0))
((0 . "LINE") (100 . "AcDbEntity") (8 . "LOUVERS") (62 . 7) (370 . 13) (100 . "AcDbLine") (10 14658.3936651584
2952.4886877828 0.0) (11 14622.3416289593 2952.4886877828 0.0))
((0 . "LINE") (100 . "AcDbEntity") (8 . "LOUVERS") (62 . 7) (370 . 13) (100 . "AcDbLine") (10 14622.3416289593
2952.4886877828 0.0) (11 14608.0316742081 2952.4886877828 0.0))
((0 . "LINE") (100 . "AcDbEntity") (8 . "LOUVERS") (62 . 7) (370 . 13) (100 . "AcDbLine") (10 14608.0316742081
2952.4886877828 0.0) (11 14569.1742081448 2952.4886877828 0.0))
((0 . "LINE") (100 . "AcDbEntity") (8 . "LOUVERS") (62 . 7) (370 . 13) (100 . "AcDbLine") (10 14569.1742081448
2952.4886877828 0.0) (11 14522.2058823529 2952.4886877828 0.0))
((0 . "LINE") (100 . "AcDbEntity") (8 . "LOUVERS") (62 . 7) (370 . 13) (100 . "AcDbLine") (10 14522.2058823529
2952.4886877828 0.0) (11 14506.2443438914 2952.4886877828 0.0))
((0 . "LINE") (100 . "AcDbEntity") (8 . "LOUVERS") (62 . 7) (370 . 13) (100 . "AcDbLine") (10 14506.2443438914
2952.4886877828 0.0) (11 14466.5045248869 2952.4886877828 0.0))
((0 . "LINE") (100 . "AcDbEntity") (8 . "LOUVERS") (62 . 7) (370 . 13) (100 . "AcDbLine") (10 14466.5045248869
2952.4886877828 0.0) (11 14446.9343891403 2952.4886877828 0.0))
((0 . "LINE") (100 . "AcDbEntity") (8 . "LOUVERS") (62 . 7) (370 . 13) (100 . "AcDbLine") (10 14446.9343891403
2952.4886877828 0.0) (11 14408.2239819005 2952.4886877828 0.0))
((0 . "LINE") (100 . "AcDbEntity") (8 . "LOUVERS") (62 . 7) (370 . 13) (100 . "AcDbLine") (10 14408.2239819005
2952.4886877828 0.0) (11 14391.4366515837 2952.4886877828 0.0))
((0 . "LINE") (100 . "AcDbEntity") (8 . "LOUVERS") (62 . 7) (370 . 13) (100 . "AcDbLine") (10 14391.4366515837
2952.4886877828 0.0) (11 14347.5904977376 2952.4886877828 0.0))
((0 . "LINE") (100 . "AcDbEntity") (8 . "LOUVERS") (62 . 7) (370 . 13) (100 . "AcDbLine") (10 14347.5904977376
2952.4886877828 0.0) (11 14308.834841629 2952.4886877828 0.0))
((0 . "LINE") (100 . "AcDbEntity") (8 . "LOUVERS") (62 . 7) (370 . 13) (100 . "AcDbLine") (10 14308.834841629
2952.4886877828 0.0) (11 14279.1742081448 2952.4886877828 0.0))
((0 . "LINE") (100 . "AcDbEntity") (8 . "LOUVERS") (62 . 7) (370 . 13) (100 . "AcDbLine") (10 14279.1742081448
2952.4886877828 0.0) (11 14231.8552036199 2952.4886877828 0.0))
((0 . "LINE") (100 . "AcDbEntity") (8 . "LOUVERS") (62 . 7) (370 . 13) (100 . "AcDbLine") (10 14231.8552036199
2952.4886877828 0.0) (11 14209.5248868778 2952.4886877828 0.0))
((0 . "LINE") (100 . "AcDbEntity") (8 . "LOUVERS") (62 . 7) (370 . 13) (100 . "AcDbLine") (10 14209.5248868778
2952.4886877828 0.0) (11 14171.6968325792 2952.4886877828 0.0))
((0 . "LINE") (100 . "AcDbEntity") (8 . "LOUVERS") (62 . 7) (370 . 13) (100 . "AcDbLine") (10 14171.6968325792
2952.4886877828 0.0) (11 14142.7036199095 2952.4886877828 0.0))
((0 . "LINE") (100 . "AcDbEntity") (8 . "LOUVERS") (62 . 7) (370 . 13) (100 . "AcDbLine") (10 14142.7036199095
2952.4886877828 0.0) (11 14109.8190045249 2952.4886877828 0.0))
((0 . "LINE") (100 . "AcDbEntity") (8 . "LOUVERS") (62 . 7) (370 . 13) (100 . "AcDbLine") (10 14109.8190045249
2952.4886877828 0.0) (11 14082.8846153846 2952.4886877828 0.0))
((0 . "LINE") (100 . "AcDbEntity") (8 . "LOUVERS") (62 . 7) (370 . 13) (100 . "AcDbLine") (10 14082.8846153846
2952.4886877828 0.0) (11 14027.9298642534 2952.4886877828 0.0))
((0 . "LINE") (100 . "AcDbEntity") (8 . "LOUVERS") (62 . 7) (370 . 13) (100 . "AcDbLine") (10 14027.9298642534
2952.4886877828 0.0) (11 13991.7081447964 2952.4886877828 0.0))
((0 . "LINE") (100 . "AcDbEntity") (8 . "LOUVERS") (62 . 7) (370 . 13) (100 . "AcDbLine") (10 13991.7081447964
2952.4886877828 0.0) (11 13954.7850678733 2952.4886877828 0.0))
((0 . "LINE") (100 . "AcDbEntity") (8 . "LOUVERS") (62 . 7) (370 . 13) (100 . "AcDbLine") (10 13954.7850678733
2952.4886877828 0.0) (11 13923.5520361991 2952.4886877828 0.0))
((0 . "LINE") (100 . "AcDbEntity") (8 . "LOUVERS") (62 . 7) (370 . 13) (100 . "AcDbLine") (10 13923.5520361991
2952.4886877828 0.0) (11 13887.5791855204 2952.4886877828 0.0))
((0 . "LINE") (100 . "AcDbEntity") (8 . "LOUVERS") (62 . 7) (370 . 13) (100 . "AcDbLine") (10 13887.5791855204
2952.4886877828 0.0) (11 13857.6583710407 2952.4886877828 0.0))
((0 . "LINE") (100 . "AcDbEntity") (8 . "LOUVERS") (62 . 7) (370 . 13) (100 . "AcDbLine") (10 13857.6583710407
2952.4886877828 0.0) (11 13824.4796380091 2952.4886877828 0.0))
((0 . "LINE") (100 . "AcDbEntity") (8 . "LOUVERS") (62 . 7) (370 . 13) (100 . "AcDbLine") (10 13824.4796380091
2952.4886877828 0.0) (11 13791.9117647059 2952.4886877828 0.0))
((0 . "LINE") (100 . "AcDbEntity") (8 . "LOUVERS") (62 . 7) (370 . 13) (100 . "AcDbLine") (10 13791.9117647059
2952.4886877828 0.0) (11 13757.5113122172 2952.4886877828 0.0))
((0 . "LINE") (100 . "AcDbEntity") (8 . "LOUVERS") (62 . 7) (370 . 13) (100 . "AcDbLine") (10 13757.5113122172
2952.4886877828 0.0) (11 13722.0814479638 2952.4886877828 0.0))
((0 . "LINE") (100 . "AcDbEntity") (8 . "LOUVERS") (62 . 7) (370 . 13) (100 . "AcDbLine") (10 13722.0814479638
2952.4886877828 0.0) (11 13679.6832579186 2952.4886877828 0.0))
((0 . "LINE") (100 . "AcDbEntity") (8 . "LOUVERS") (62 . 7) (370 . 13) (100 . "AcDbLine") (10 13679.6832579186
2952.4886877828 0.0) (11 13641.4479638009 2952.4886877828 0.0))
((0 . "LINE") (100 . "AcDbEntity") (8 . "LOUVERS") (62 . 7) (370 . 13) (100 . "AcDbLine") (10 13641.4479638009
2952.4886877828 0.0) (11 13600.3959276018 2952.4886877828 0.0))
((0 . "LINE") (100 . "AcDbEntity") (8 . "LOUVERS") (62 . 7) (370 . 13) (100 . "AcDbLine") (10 13600.3959276018
2952.4886877828 0.0) (11 13570.4411764706 2952.4886877828 0.0))
((0 . "LINE") (100 . "AcDbEntity") (8 . "LOUVERS") (62 . 7) (370 . 13) (100 . "AcDbLine") (10 13570.4411764706
2952.4886877828 0.0) (11 13531.221719457 2952.4886877828 0.0))
((0 . "LINE") (100 . "AcDbEntity") (8 . "LOUVERS") (62 . 7) (370 . 13) (100 . "AcDbLine") (10 13531.221719457
2952.4886877828 0.0) (11 13498.2918552036 2952.4886877828 0.0))
((0 . "LINE") (100 . "AcDbEntity") (8 . "LOUVERS") (62 . 7) (370 . 13) (100 . "AcDbLine") (10 13498.2918552036
2952.4886877828 0.0) (11 13451.7307692308 2952.4886877828 0.0))
((0 . "LINE") (100 . "AcDbEntity") (8 . "LOUVERS") (62 . 7) (370 . 13) (100 . "AcDbLine") (10 13451.7307692308
2952.4886877828 0.0) (11 13416.2895927602 2952.4886877828 0.0))
((0 . "LINE") (100 . "AcDbEntity") (8 . "LOUVERS") (62 . 7) (370 . 13) (100 . "AcDbLine") (10 13416.2895927602
2952.4886877828 0.0) (11 13379.1628959276 2952.4886877828 0.0))
((0 . "LINE") (100 . "AcDbEntity") (8 . "LOUVERS") (62 . 7) (370 . 13) (100 . "AcDbLine") (10 13379.1628959276
2952.4886877828 0.0) (11 13333.257918552 2952.4886877828 0.0))
((0 . "LINE") (100 . "AcDbEntity") (8 . "LOUVERS") (62 . 7) (370 . 13) (100 . "AcDbLine") (10 13333.257918552
2952.4886877828 0.0) (11 13296.2895927602 2952.4886877828 0.0))
((0 . "LINE") (100 . "AcDbEntity") (8 . "LOUVERS") (62 . 7) (370 . 13) (100 . "AcDbLine") (10 13296.2895927602
2952.4886877828 0.0) (11 13246.8778280543 2952.4886877828 0.0))
((0 . "LINE") (100 . "AcDbEntity") (8 . "LOUVERS") (62 . 7) (370 . 13) (100 . "AcDbLine") (10 13246.8778280543
2952.4886877828 0.0) (11 13212.6696832579 2952.4886877828 0.0))
((0 . "LINE") (100 . "AcDbEntity") (8 . "LOUVERS") (62 . 7) (370 . 13) (100 . "AcDbLine") (10 13212.6696832579
2952.4886877828 0.0) (11 13212.6696832579 3212.6696832579 0.0))
((0 . "LINE") (100 . "AcDbEntity") (8 . "LOUVERS") (62 . 7) (370 . 13) (100 . "AcDbLine") (10 13246.8778280543
3212.6696832579 0.0) (11 13246.8778280543 2952.4886877828 0.0))
((0 . "LINE") (100 . "AcDbEntity") (8 . "LOUVERS") (62 . 7) (370 . 13) (100 . "AcDbLine") (10 13296.2895927602
3212.6696832579 0.0) (11 13296.2895927602 2952.4886877828 0.0))
((0 . "LINE") (100 . "AcDbEntity") (8 . "LOUVERS") (62 . 7) (370 . 13) (100 . "AcDbLine") (10 13333.257918552
3212.6696832579 0.0) (11 13333.257918552 2952.4886877828 0.0))
((0 . "LINE") (100 . "AcDbEntity") (8 . "LOUVERS") (62 . 7) (370 . 13) (100 . "AcDbLine") (10 13379.1628959276
3212.6696832579 0.0) (11 13379.1628959276 2952.4886877828 0.0))
((0 . "LINE") (100 . "AcDbEntity") (8 . "LOUVERS") (62 . 7) (370 . 13) (100 . "AcDbLine") (10 13416.2895927602
3212.6696832579 0.0) (11 13416.2895927602 2952.4886877828 0.0))
((0 . "LINE") (100 . "AcDbEntity") (8 . "LOUVERS") (62 . 7) (370 . 13) (100 . "AcDbLine") (10 13451.7307692308
3212.6696832579 0.0) (11 13451.7307692308 2952.4886877828 0.0))
((0 . "LINE") (100 . "AcDbEntity") (8 . "LOUVERS") (62 . 7) (370 . 13) (100 . "AcDbLine") (10 13498.2918552036
3212.6696832579 0.0) (11 13498.2918552036 2952.4886877828 0.0))
((0 . "LINE") (100 . "AcDbEntity") (8 . "LOUVERS") (62 . 7) (370 . 13) (100 . "AcDbLine") (10 13531.221719457
3212.6696832579 0.0) (11 13531.221719457 2952.4886877828 0.0))
((0 . "LINE") (100 . "AcDbEntity") (8 . "LOUVERS") (62 . 7) (370 . 13) (100 . "AcDbLine") (10 13570.4411764706
3212.6696832579 0.0) (11 13570.4411764706 2952.4886877828 0.0))
((0 . "LINE") (100 . "AcDbEntity") (8 . "LOUVERS") (62 . 7) (370 . 13) (100 . "AcDbLine") (10 13600.3959276018
3212.6696832579 0.0) (11 13600.3959276018 2952.4886877828 0.0))
((0 . "LINE") (100 . "AcDbEntity") (8 . "LOUVERS") (62 . 7) (370 . 13) (100 . "AcDbLine") (10 13641.4479638009
3212.6696832579 0.0) (11 13641.4479638009 2952.4886877828 0.0))
((0 . "LINE") (100 . "AcDbEntity") (8 . "LOUVERS") (62 . 7) (370 . 13) (100 . "AcDbLine") (10 13679.6832579186
3212.6696832579 0.0) (11 13679.6832579186 2952.4886877828 0.0))
((0 . "LINE") (100 . "AcDbEntity") (8 . "LOUVERS") (62 . 7) (370 . 13) (100 . "AcDbLine") (10 13722.0814479638
3212.6696832579 0.0) (11 13722.0814479638 2952.4886877828 0.0))
((0 . "LINE") (100 . "AcDbEntity") (8 . "LOUVERS") (62 . 7) (370 . 13) (100 . "AcDbLine") (10 13757.5113122172
3212.6696832579 0.0) (11 13757.5113122172 2952.4886877828 0.0))
((0 . "LINE") (100 . "AcDbEntity") (8 . "LOUVERS") (62 . 7) (370 . 13) (100 . "AcDbLine") (10 13791.9117647059
3212.6696832579 0.0) (11 13791.9117647059 2952.4886877828 0.0))
((0 . "LINE") (100 . "AcDbEntity") (8 . "LOUVERS") (62 . 7) (370 . 13) (100 . "AcDbLine") (10 13824.4796380091
3212.6696832579 0.0) (11 13824.4796380091 2952.4886877828 0.0))
((0 . "LINE") (100 . "AcDbEntity") (8 . "LOUVERS") (62 . 7) (370 . 13) (100 . "AcDbLine") (10 13857.6583710407
3212.6696832579 0.0) (11 13857.6583710407 2952.4886877828 0.0))
((0 . "LINE") (100 . "AcDbEntity") (8 . "LOUVERS") (62 . 7) (370 . 13) (100 . "AcDbLine") (10 13887.5791855204
3212.6696832579 0.0) (11 13887.5791855204 2952.4886877828 0.0))
((0 . "LINE") (100 . "AcDbEntity") (8 . "LOUVERS") (62 . 7) (370 . 13) (100 . "AcDbLine") (10 13923.5520361991
3212.6696832579 0.0) (11 13923.5520361991 2952.4886877828 0.0))
((0 . "LINE") (100 . "AcDbEntity") (8 . "LOUVERS") (62 . 7) (370 . 13) (100 . "AcDbLine") (10 13954.7850678733
3212.6696832579 0.0) (11 13954.7850678733 2952.4886877828 0.0))
((0 . "LINE") (100 . "AcDbEntity") (8 . "LOUVERS") (62 . 7) (370 . 13) (100 . "AcDbLine") (10 13991.7081447964
3212.6696832579 0.0) (11 13991.7081447964 2952.4886877828 0.0))
((0 . "LINE") (100 . "AcDbEntity") (8 . "LOUVERS") (62 . 7) (370 . 13) (100 . "AcDbLine") (10 14027.9298642534
3212.6696832579 0.0) (11 14027.9298642534 2952.4886877828 0.0))
((0 . "LINE") (100 . "AcDbEntity") (8 . "LOUVERS") (62 . 7) (370 . 13) (100 . "AcDbLine") (10 14082.8846153846
3212.6696832579 0.0) (11 14082.8846153846 2952.4886877828 0.0))
((0 . "LINE") (100 . "AcDbEntity") (8 . "LOUVERS") (62 . 7) (370 . 13) (100 . "AcDbLine") (10 14109.8190045249
3212.6696832579 0.0) (11 14109.8190045249 2952.4886877828 0.0))
((0 . "LINE") (100 . "AcDbEntity") (8 . "LOUVERS") (62 . 7) (370 . 13) (100 . "AcDbLine") (10 14142.7036199095
3212.6696832579 0.0) (11 14142.7036199095 2952.4886877828 0.0))
((0 . "LINE") (100 . "AcDbEntity") (8 . "LOUVERS") (62 . 7) (370 . 13) (100 . "AcDbLine") (10 14171.6968325792
3212.6696832579 0.0) (11 14171.6968325792 2952.4886877828 0.0))
((0 . "LINE") (100 . "AcDbEntity") (8 . "LOUVERS") (62 . 7) (370 . 13) (100 . "AcDbLine") (10 14209.5248868778
3212.6696832579 0.0) (11 14209.5248868778 2952.4886877828 0.0))
((0 . "LINE") (100 . "AcDbEntity") (8 . "LOUVERS") (62 . 7) (370 . 13) (100 . "AcDbLine") (10 14231.8552036199
3212.6696832579 0.0) (11 14231.8552036199 2952.4886877828 0.0))
((0 . "LINE") (100 . "AcDbEntity") (8 . "LOUVERS") (62 . 7) (370 . 13) (100 . "AcDbLine") (10 14279.1742081448
3212.6696832579 0.0) (11 14279.1742081448 2952.4886877828 0.0))
((0 . "LINE") (100 . "AcDbEntity") (8 . "LOUVERS") (62 . 7) (370 . 13) (100 . "AcDbLine") (10 14308.834841629
3212.6696832579 0.0) (11 14308.834841629 2952.4886877828 0.0))
((0 . "LINE") (100 . "AcDbEntity") (8 . "LOUVERS") (62 . 7) (370 . 13) (100 . "AcDbLine") (10 14347.5904977376
3212.6696832579 0.0) (11 14347.5904977376 2952.4886877828 0.0))
((0 . "LINE") (100 . "AcDbEntity") (8 . "LOUVERS") (62 . 7) (370 . 13) (100 . "AcDbLine") (10 14391.4366515837
3212.6696832579 0.0) (11 14391.4366515837 2952.4886877828 0.0))
((0 . "LINE") (100 . "AcDbEntity") (8 . "LOUVERS") (62 . 7) (370 . 13) (100 . "AcDbLine") (10 14408.2239819005
3212.6696832579 0.0) (11 14408.2239819005 2952.4886877828 0.0))
((0 . "LINE") (100 . "AcDbEntity") (8 . "LOUVERS") (62 . 7) (370 . 13) (100 . "AcDbLine") (10 14446.9343891403
3212.6696832579 0.0) (11 14446.9343891403 2952.4886877828 0.0))
((0 . "LINE") (100 . "AcDbEntity") (8 . "LOUVERS") (62 . 7) (370 . 13) (100 . "AcDbLine") (10 14466.5045248869
3212.6696832579 0.0) (11 14466.5045248869 2952.4886877828 0.0))
((0 . "LINE") (100 . "AcDbEntity") (8 . "LOUVERS") (62 . 7) (370 . 13) (100 . "AcDbLine") (10 14506.2443438914
3212.6696832579 0.0) (11 14506.2443438914 2952.4886877828 0.0))
((0 . "LINE") (100 . "AcDbEntity") (8 . "LOUVERS") (62 . 7) (370 . 13) (100 . "AcDbLine") (10 14522.2058823529
3212.6696832579 0.0) (11 14522.2058823529 2952.4886877828 0.0))
((0 . "LINE") (100 . "AcDbEntity") (8 . "LOUVERS") (62 . 7) (370 . 13) (100 . "AcDbLine") (10 14569.1742081448
3212.6696832579 0.0) (11 14569.1742081448 2952.4886877828 0.0))
((0 . "LINE") (100 . "AcDbEntity") (8 . "LOUVERS") (62 . 7) (370 . 13) (100 . "AcDbLine") (10 14608.0316742081
3212.6696832579 0.0) (11 14608.0316742081 2952.4886877828 0.0))
((0 . "LINE") (100 . "AcDbEntity") (8 . "LOUVERS") (62 . 7) (370 . 13) (100 . "AcDbLine") (10 14622.3416289593
3212.6696832579 0.0) (11 14622.3416289593 2952.4886877828 0.0))
((0 . "LINE") (100 . "AcDbEntity") (8 . "LOUVERS") (62 . 7) (370 . 13) (100 . "AcDbLine") (10 14658.3936651584
3212.6696832579 0.0) (11 14658.3936651584 2952.4886877828 0.0))
((0 . "LINE") (100 . "AcDbEntity") (8 . "LOUVERS") (62 . 7) (370 . 13) (100 . "AcDbLine") (10 14687.5113122172
3212.6696832579 0.0) (11 14687.5113122172 2952.4886877828 0.0))
((0 . "LINE") (100 . "AcDbEntity") (8 . "LOUVERS") (62 . 7) (370 . 13) (100 . "AcDbLine") (10 14734.3552036199
3212.6696832579 0.0) (11 14734.3552036199 2952.4886877828 0.0))
((0 . "LINE") (100 . "AcDbEntity") (8 . "LOUVERS") (62 . 7) (370 . 13) (100 . "AcDbLine") (10 14774.5475113122
3212.6696832579 0.0) (11 14774.5475113122 2952.4886877828 0.0))
((0 . "LINE") (100 . "AcDbEntity") (8 . "LOUVERS") (62 . 7) (370 . 13) (100 . "AcDbLine") (10 14802.0475113122
3212.6696832579 0.0) (11 14802.0475113122 2952.4886877828 0.0))
((0 . "LINE") (100 . "AcDbEntity") (8 . "LOUVERS") (62 . 7) (370 . 13) (100 . "AcDbLine") (10 14829.8755656109
3212.6696832579 0.0) (11 14829.8755656109 2952.4886877828 0.0))
((0 . "LINE") (100 . "AcDbEntity") (8 . "LOUVERS") (62 . 7) (370 . 13) (100 . "AcDbLine") (10 14864.8303167421
3212.6696832579 0.0) (11 14864.8303167421 2952.4886877828 0.0))
((0 . "LINE") (100 . "AcDbEntity") (8 . "LOUVERS") (62 . 7) (370 . 13) (100 . "AcDbLine") (10 14935.5090497738
3212.6696832579 0.0) (11 14935.5090497738 2952.4886877828 0.0))
((0 . "LINE") (100 . "AcDbEntity") (8 . "LOUVERS") (62 . 7) (370 . 13) (100 . "AcDbLine") (10 14997.9751131222
3212.6696832579 0.0) (11 14997.9751131222 2952.4886877828 0.0))
((0 . "LINE") (100 . "AcDbEntity") (8 . "LOUVERS") (62 . 7) (370 . 13) (100 . "AcDbLine") (10 15031.9004524887
3212.6696832579 0.0) (11 15031.9004524887 2952.4886877828 0.0))
((0 . "LINE") (100 . "AcDbEntity") (8 . "LOUVERS") (62 . 7) (370 . 13) (100 . "AcDbLine") (10 15067.2963800905
3212.6696832579 0.0) (11 15067.2963800905 2952.4886877828 0.0))
((0 . "LINE") (100 . "AcDbEntity") (8 . "LOUVERS") (62 . 7) (370 . 13) (100 . "AcDbLine") (10 15102.6244343891
3212.6696832579 0.0) (11 15102.6244343891 2952.4886877828 0.0))
((0 . "LINE") (100 . "AcDbEntity") (8 . "LOUVERS") (62 . 7) (370 . 13) (100 . "AcDbLine") (10 15143.0995475113
3212.6696832579 0.0) (11 15143.0995475113 2952.4886877828 0.0))
((0 . "LINE") (100 . "AcDbEntity") (8 . "LOUVERS") (62 . 7) (370 . 13) (100 . "AcDbLine") (10 15178.778280543
3212.6696832579 0.0) (11 15178.778280543 2952.4886877828 0.0))
((0 . "LINE") (100 . "AcDbEntity") (8 . "LOUVERS") (62 . 7) (370 . 13) (100 . "AcDbLine") (10 15215.8257918552
3212.6696832579 0.0) (11 15215.8257918552 2952.4886877828 0.0))
((0 . "LINE") (100 . "AcDbEntity") (8 . "LOUVERS") (62 . 7) (370 . 13) (100 . "AcDbLine") (10 15251.1085972851
3212.6696832579 0.0) (11 15251.1085972851 2952.4886877828 0.0))
((0 . "LINE") (100 . "AcDbEntity") (8 . "LOUVERS") (62 . 7) (370 . 13) (100 . "AcDbLine") (10 15287.8280542986
3212.6696832579 0.0) (11 15287.8280542986 2952.4886877828 0.0))
((0 . "LINE") (100 . "AcDbEntity") (8 . "LOUVERS") (62 . 7) (370 . 13) (100 . "AcDbLine") (10 15325.3846153846
3212.6696832579 0.0) (11 15325.3846153846 2952.4886877828 0.0))
((0 . "LINE") (100 . "AcDbEntity") (8 . "LOUVERS") (62 . 7) (370 . 13) (100 . "AcDbLine") (10 15360.9841628959
3212.6696832579 0.0) (11 15360.9841628959 2952.4886877828 0.0))
((0 . "LINE") (100 . "AcDbEntity") (8 . "LOUVERS") (62 . 7) (370 . 13) (100 . "AcDbLine") (10 15395.5429864253
3212.6696832579 0.0) (11 15395.5429864253 2952.4886877828 0.0))
((0 . "LINE") (100 . "AcDbEntity") (8 . "LOUVERS") (62 . 7) (370 . 13) (100 . "AcDbLine") (10 15430.7466063348
3212.6696832579 0.0) (11 15430.7466063348 2952.4886877828 0.0))
((0 . "LINE") (100 . "AcDbEntity") (8 . "LOUVERS") (62 . 7) (370 . 13) (100 . "AcDbLine") (10 15463.2352941176
3212.6696832579 0.0) (11 15463.2352941176 2952.4886877828 0.0))
((0 . "LINE") (100 . "AcDbEntity") (8 . "LOUVERS") (62 . 7) (370 . 13) (100 . "AcDbLine") (10 15509.4343891403
3212.6696832579 0.0) (11 15509.4343891403 2952.4886877828 0.0))
((0 . "LINE") (100 . "AcDbEntity") (8 . "LOUVERS") (62 . 7) (370 . 13) (100 . "AcDbLine") (10 15541.4819004525
3212.6696832579 0.0) (11 15541.4819004525 2952.4886877828 0.0))
((0 . "LINE") (100 . "AcDbEntity") (8 . "LOUVERS") (62 . 7) (370 . 13) (100 . "AcDbLine") (10 15579.1176470588
3212.6696832579 0.0) (11 15579.1176470588 2952.4886877828 0.0))
((0 . "LINE") (100 . "AcDbEntity") (8 . "LOUVERS") (62 . 7) (370 . 13) (100 . "AcDbLine") (10 15612.036199095
3212.6696832579 0.0) (11 15612.036199095 2952.4886877828 0.0))
((0 . "LINE") (100 . "AcDbEntity") (8 . "LOUVERS") (62 . 7) (370 . 13) (100 . "AcDbLine") (10 15644.6606334842
3212.6696832579 0.0) (11 15644.6606334842 2952.4886877828 0.0))
((0 . "LINE") (100 . "AcDbEntity") (8 . "LOUVERS") (62 . 7) (370 . 13) (100 . "AcDbLine") (10 15681.0180995475
3212.6696832579 0.0) (11 15681.0180995475 2952.4886877828 0.0))
((0 . "LINE") (100 . "AcDbEntity") (8 . "LOUVERS") (62 . 7) (370 . 13) (100 . "AcDbLine") (10 15698.7895927602
3212.6696832579 0.0) (11 15698.7895927602 2952.4886877828 0.0))
((0 . "LINE") (100 . "AcDbEntity") (8 . "LOUVERS") (62 . 7) (370 . 13) (100 . "AcDbLine") (10 15738.0542986425
3212.6696832579 0.0) (11 15738.0542986425 2952.4886877828 0.0))
((0 . "LINE") (100 . "AcDbEntity") (8 . "LOUVERS") (62 . 7) (370 . 13) (100 . "AcDbLine") (10 15756.8552036199
3212.6696832579 0.0) (11 15756.8552036199 2952.4886877828 0.0))
((0 . "LINE") (100 . "AcDbEntity") (8 . "LOUVERS") (62 . 7) (370 . 13) (100 . "AcDbLine") (10 15802.963800905
3212.6696832579 0.0) (11 15802.963800905 2952.4886877828 0.0))
((0 . "LINE") (100 . "AcDbEntity") (8 . "LOUVERS") (62 . 7) (370 . 13) (100 . "AcDbLine") (10 15828.6312217195
3212.6696832579 0.0) (11 15828.6312217195 2952.4886877828 0.0))
((0 . "LINE") (100 . "AcDbEntity") (8 . "LOUVERS") (62 . 7) (370 . 13) (100 . "AcDbLine") (10 15872.0814479638
3212.6696832579 0.0) (11 15872.0814479638 2952.4886877828 0.0))
((0 . "LINE") (100 . "AcDbEntity") (8 . "LOUVERS") (62 . 7) (370 . 13) (100 . "AcDbLine") (10 15901.0633484163
3212.6696832579 0.0) (11 15901.0633484163 2952.4886877828 0.0))
((0 . "LINE") (100 . "AcDbEntity") (8 . "LOUVERS") (62 . 7) (370 . 13) (100 . "AcDbLine") (10 13506.7873303167
2194.5701357466 0.0) (11 13516.9230769231 2194.5701357466 0.0))
((0 . "LINE") (100 . "AcDbEntity") (8 . "LOUVERS") (62 . 7) (370 . 13) (100 . "AcDbLine") (10 13516.9230769231
2194.5701357466 0.0) (11 13551.4140271493 2194.5701357466 0.0))
((0 . "LINE") (100 . "AcDbEntity") (8 . "LOUVERS") (62 . 7) (370 . 13) (100 . "AcDbLine") (10 13551.4140271493
2194.5701357466 0.0) (11 13575.3054298643 2194.5701357466 0.0))
((0 . "LINE") (100 . "AcDbEntity") (8 . "LOUVERS") (62 . 7) (370 . 13) (100 . "AcDbLine") (10 13575.3054298643
2194.5701357466 0.0) (11 13608.4049773756 2194.5701357466 0.0))
((0 . "LINE") (100 . "AcDbEntity") (8 . "LOUVERS") (62 . 7) (370 . 13) (100 . "AcDbLine") (10 13608.4049773756
2194.5701357466 0.0) (11 13639.9773755656 2194.5701357466 0.0))
((0 . "LINE") (100 . "AcDbEntity") (8 . "LOUVERS") (62 . 7) (370 . 13) (100 . "AcDbLine") (10 13639.9773755656
2194.5701357466 0.0) (11 13674.2647058824 2194.5701357466 0.0))
((0 . "LINE") (100 . "AcDbEntity") (8 . "LOUVERS") (62 . 7) (370 . 13) (100 . "AcDbLine") (10 13674.2647058824
2194.5701357466 0.0) (11 13701.7081447964 2194.5701357466 0.0))
((0 . "LINE") (100 . "AcDbEntity") (8 . "LOUVERS") (62 . 7) (370 . 13) (100 . "AcDbLine") (10 13701.7081447964
2194.5701357466 0.0) (11 13731.2104072398 2194.5701357466 0.0))
((0 . "LINE") (100 . "AcDbEntity") (8 . "LOUVERS") (62 . 7) (370 . 13) (100 . "AcDbLine") (10 13731.2104072398
2194.5701357466 0.0) (11 13766.1990950226 2194.5701357466 0.0))
((0 . "LINE") (100 . "AcDbEntity") (8 . "LOUVERS") (62 . 7) (370 . 13) (100 . "AcDbLine") (10 13766.1990950226
2194.5701357466 0.0) (11 13812.2171945701 2194.5701357466 0.0))
((0 . "LINE") (100 . "AcDbEntity") (8 . "LOUVERS") (62 . 7) (370 . 13) (100 . "AcDbLine") (10 13812.2171945701
2194.5701357466 0.0) (11 13812.2171945701 2183.257918552 0.0))
((0 . "LINE") (100 . "AcDbEntity") (8 . "LOUVERS") (62 . 7) (370 . 13) (100 . "AcDbLine") (10 13812.2171945701
2183.257918552 0.0) (11 13812.2171945701 1125.8115271493 0.0))
((0 . "LINE") (100 . "AcDbEntity") (8 . "LOUVERS") (62 . 7) (370 . 13) (100 . "AcDbLine") (10 13506.7873303167
1247.3207918552 0.0) (11 13506.7873303167 2194.5701357466 0.0))
((0 . "LINE") (100 . "AcDbEntity") (8 . "LOUVERS") (62 . 7) (370 . 13) (100 . "AcDbLine") (10 13516.9230769231
2194.5701357466 0.0) (11 13516.9230769231 1253.1888574661 0.0))
((0 . "LINE") (100 . "AcDbEntity") (8 . "LOUVERS") (62 . 7) (370 . 13) (100 . "AcDbLine") (10 13551.4140271493
2194.5701357466 0.0) (11 13551.4140271493 1259.0914479638 0.0))
((0 . "LINE") (100 . "AcDbEntity") (8 . "LOUVERS") (62 . 7) (370 . 13) (100 . "AcDbLine") (10 13575.3054298643
2194.5701357466 0.0) (11 13575.3054298643 1241.4872624434 0.0))
((0 . "LINE") (100 . "AcDbEntity") (8 . "LOUVERS") (62 . 7) (370 . 13) (100 . "AcDbLine") (10 13608.4049773756
2194.5701357466 0.0) (11 13608.4049773756 1217.0981221719 0.0))
((0 . "LINE") (100 . "AcDbEntity") (8 . "LOUVERS") (62 . 7) (370 . 13) (100 . "AcDbLine") (10 13639.9773755656
2194.5701357466 0.0) (11 13639.9773755656 1193.8342420814 0.0))
((0 . "LINE") (100 . "AcDbEntity") (8 . "LOUVERS") (62 . 7) (370 . 13) (100 . "AcDbLine") (10 13674.2647058824
2194.5701357466 0.0) (11 13674.2647058824 1168.56989819 0.0))
((0 . "LINE") (100 . "AcDbEntity") (8 . "LOUVERS") (62 . 7) (370 . 13) (100 . "AcDbLine") (10 13701.7081447964
2194.5701357466 0.0) (11 13701.7081447964 1148.3484162896 0.0))
((0 . "LINE") (100 . "AcDbEntity") (8 . "LOUVERS") (62 . 7) (370 . 13) (100 . "AcDbLine") (10 13731.2104072398
2194.5701357466 0.0) (11 13731.2104072398 1126.6099095023 0.0))
((0 . "LINE") (100 . "AcDbEntity") (8 . "LOUVERS") (62 . 7) (370 . 13) (100 . "AcDbLine") (10 13766.1990950226
2194.5701357466 0.0) (11 13766.1990950226 1111.8060180995 0.0))
((0 . "LINE") (100 . "AcDbEntity") (8 . "LOUVERS") (62 . 7) (370 . 13) (100 . "AcDbLine") (10 15361.9909502262
2194.5701357466 0.0) (11 15409.1063348416 2194.5701357466 0.0))
((0 . "LINE") (100 . "AcDbEntity") (8 . "LOUVERS") (62 . 7) (370 . 13) (100 . "AcDbLine") (10 15409.1063348416
2194.5701357466 0.0) (11 15438.2126696833 2194.5701357466 0.0))
((0 . "LINE") (100 . "AcDbEntity") (8 . "LOUVERS") (62 . 7) (370 . 13) (100 . "AcDbLine") (10 15438.2126696833
2194.5701357466 0.0) (11 15487.556561086 2194.5701357466 0.0))
((0 . "LINE") (100 . "AcDbEntity") (8 . "LOUVERS") (62 . 7) (370 . 13) (100 . "AcDbLine") (10 15487.556561086
2194.5701357466 0.0) (11 15528.0429864253 2194.5701357466 0.0))
((0 . "LINE") (100 . "AcDbEntity") (8 . "LOUVERS") (62 . 7) (370 . 13) (100 . "AcDbLine") (10 15528.0429864253
2194.5701357466 0.0) (11 15554.6606334842 2194.5701357466 0.0))
((0 . "LINE") (100 . "AcDbEntity") (8 . "LOUVERS") (62 . 7) (370 . 13) (100 . "AcDbLine") (10 15554.6606334842
2194.5701357466 0.0) (11 15588.257918552 2194.5701357466 0.0))
((0 . "LINE") (100 . "AcDbEntity") (8 . "LOUVERS") (62 . 7) (370 . 13) (100 . "AcDbLine") (10 15588.257918552
2194.5701357466 0.0) (11 15613.371040724 2194.5701357466 0.0))
((0 . "LINE") (100 . "AcDbEntity") (8 . "LOUVERS") (62 . 7) (370 . 13) (100 . "AcDbLine") (10 15613.371040724
2194.5701357466 0.0) (11 15664.6606334842 2194.5701357466 0.0))
((0 . "LINE") (100 . "AcDbEntity") (8 . "LOUVERS") (62 . 7) (370 . 13) (100 . "AcDbLine") (10 15664.6606334842
2194.5701357466 0.0) (11 15690.0452488688 2194.5701357466 0.0))
((0 . "LINE") (100 . "AcDbEntity") (8 . "LOUVERS") (62 . 7) (370 . 13) (100 . "AcDbLine") (10 15690.0452488688
2194.5701357466 0.0) (11 15690.0452488688 1171.7075452489 0.0))
((0 . "LINE") (100 . "AcDbEntity") (8 . "LOUVERS") (62 . 7) (370 . 13) (100 . "AcDbLine") (10 15361.9909502262
1166.7009502262 0.0) (11 15361.9909502262 2183.257918552 0.0))
((0 . "LINE") (100 . "AcDbEntity") (8 . "LOUVERS") (62 . 7) (370 . 13) (100 . "AcDbLine") (10 15361.9909502262
2183.257918552 0.0) (11 15361.9909502262 2194.5701357466 0.0))
((0 . "LINE") (100 . "AcDbEntity") (8 . "LOUVERS") (62 . 7) (370 . 13) (100 . "AcDbLine") (10 15409.1063348416
2194.5701357466 0.0) (11 15409.1063348416 1198.8250678733 0.0))
((0 . "LINE") (100 . "AcDbEntity") (8 . "LOUVERS") (62 . 7) (370 . 13) (100 . "AcDbLine") (10 15438.2126696833
2194.5701357466 0.0) (11 15438.2126696833 1218.6703054299 0.0))
((0 . "LINE") (100 . "AcDbEntity") (8 . "LOUVERS") (62 . 7) (370 . 13) (100 . "AcDbLine") (10 15487.556561086
2194.5701357466 0.0) (11 15487.556561086 1252.3138574661 0.0))
((0 . "LINE") (100 . "AcDbEntity") (8 . "LOUVERS") (62 . 7) (370 . 13) (100 . "AcDbLine") (10 15528.0429864253
2194.5701357466 0.0) (11 15528.0429864253 1256.9719004525 0.0))
((0 . "LINE") (100 . "AcDbEntity") (8 . "LOUVERS") (62 . 7) (370 . 13) (100 . "AcDbLine") (10 15554.6606334842
2194.5701357466 0.0) (11 15554.6606334842 1242.9626131222 0.0))
((0 . "LINE") (100 . "AcDbEntity") (8 . "LOUVERS") (62 . 7) (370 . 13) (100 . "AcDbLine") (10 15588.257918552
2194.5701357466 0.0) (11 15588.257918552 1225.2798303167 0.0))
((0 . "LINE") (100 . "AcDbEntity") (8 . "LOUVERS") (62 . 7) (370 . 13) (100 . "AcDbLine") (10 15613.371040724
2194.5701357466 0.0) (11 15613.371040724 1212.06239819 0.0))
((0 . "LINE") (100 . "AcDbEntity") (8 . "LOUVERS") (62 . 7) (370 . 13) (100 . "AcDbLine") (10 15664.6606334842
2194.5701357466 0.0) (11 15664.6606334842 1185.0678733032 0.0))
((0 . "LINE") (100 . "AcDbEntity") (8 . "LOUVERS") (62 . 7) (370 . 13) (100 . "AcDbLine") (10 1018.0995475113
5180.9954751131 0.0) (11 1065.1696832579 5180.9954751131 0.0))
((0 . "LINE") (100 . "AcDbEntity") (8 . "LOUVERS") (62 . 7) (370 . 13) (100 . "AcDbLine") (10 1065.1696832579
5180.9954751131 0.0) (11 1091.3122171946 5180.9954751131 0.0))
((0 . "LINE") (100 . "AcDbEntity") (8 . "LOUVERS") (62 . 7) (370 . 13) (100 . "AcDbLine") (10 1091.3122171946
5180.9954751131 0.0) (11 1133.7443438914 5180.9954751131 0.0))
((0 . "LINE") (100 . "AcDbEntity") (8 . "LOUVERS") (62 . 7) (370 . 13) (100 . "AcDbLine") (10 1133.7443438914
5180.9954751131 0.0) (11 1190.1470588235 5180.9954751131 0.0))
((0 . "LINE") (100 . "AcDbEntity") (8 . "LOUVERS") (62 . 7) (370 . 13) (100 . "AcDbLine") (10 1190.1470588235
5180.9954751131 0.0) (11 1207.1380090498 5180.9954751131 0.0))
((0 . "LINE") (100 . "AcDbEntity") (8 . "LOUVERS") (62 . 7) (370 . 13) (100 . "AcDbLine") (10 1207.1380090498
5180.9954751131 0.0) (11 1253.1674208145 5180.9954751131 0.0))
((0 . "LINE") (100 . "AcDbEntity") (8 . "LOUVERS") (62 . 7) (370 . 13) (100 . "AcDbLine") (10 1253.1674208145
5180.9954751131 0.0) (11 1302.2737556561 5180.9954751131 0.0))
((0 . "LINE") (100 . "AcDbEntity") (8 . "LOUVERS") (62 . 7) (370 . 13) (100 . "AcDbLine") (10 1302.2737556561
5180.9954751131 0.0) (11 1321.2895927602 5180.9954751131 0.0))
((0 . "LINE") (100 . "AcDbEntity") (8 . "LOUVERS") (62 . 7) (370 . 13) (100 . "AcDbLine") (10 1321.2895927602
5180.9954751131 0.0) (11 1334.8416289593 5180.9954751131 0.0))
((0 . "LINE") (100 . "AcDbEntity") (8 . "LOUVERS") (62 . 7) (370 . 13) (100 . "AcDbLine") (10 1334.8416289593
5180.9954751131 0.0) (11 1334.8416289593 4078.3519909502 0.0))
((0 . "LINE") (100 . "AcDbEntity") (8 . "LOUVERS") (62 . 7) (370 . 13) (100 . "AcDbLine") (10 1018.0995475113
4147.232861991 0.0) (11 1018.0995475113 4457.0135746606 0.0))
((0 . "LINE") (100 . "AcDbEntity") (8 . "LOUVERS") (62 . 7) (370 . 13) (100 . "AcDbLine") (10 1018.0995475113
4457.0135746606 0.0) (11 1018.0995475113 4819.0045248869 0.0))
((0 . "LINE") (100 . "AcDbEntity") (8 . "LOUVERS") (62 . 7) (370 . 13) (100 . "AcDbLine") (10 1018.0995475113
4819.0045248869 0.0) (11 1018.0995475113 5180.9954751131 0.0))
((0 . "LINE") (100 . "AcDbEntity") (8 . "LOUVERS") (62 . 7) (370 . 13) (100 . "AcDbLine") (10 1065.1696832579
5180.9954751131 0.0) (11 1065.1696832579 4183.4406561086 0.0))
((0 . "LINE") (100 . "AcDbEntity") (8 . "LOUVERS") (62 . 7) (370 . 13) (100 . "AcDbLine") (10 1091.3122171946
5180.9954751131 0.0) (11 1091.3122171946 4203.5502941176 0.0))
((0 . "LINE") (100 . "AcDbEntity") (8 . "LOUVERS") (62 . 7) (370 . 13) (100 . "AcDbLine") (10 1133.7443438914
5180.9954751131 0.0) (11 1133.7443438914 4168.8809615385 0.0))
((0 . "LINE") (100 . "AcDbEntity") (8 . "LOUVERS") (62 . 7) (370 . 13) (100 . "AcDbLine") (10 1190.1470588235
5180.9954751131 0.0) (11 1190.1470588235 4108.1395701357 0.0))
((0 . "LINE") (100 . "AcDbEntity") (8 . "LOUVERS") (62 . 7) (370 . 13) (100 . "AcDbLine") (10 1207.1380090498
5180.9954751131 0.0) (11 1207.1380090498 4089.8416289593 0.0))
((0 . "LINE") (100 . "AcDbEntity") (8 . "LOUVERS") (62 . 7) (370 . 13) (100 . "AcDbLine") (10 1253.1674208145
5180.9954751131 0.0) (11 1253.1674208145 4052.5601357466 0.0))
((0 . "LINE") (100 . "AcDbEntity") (8 . "LOUVERS") (62 . 7) (370 . 13) (100 . "AcDbLine") (10 1302.2737556561
5180.9954751131 0.0) (11 1302.2737556561 4068.06739819 0.0))
((0 . "LINE") (100 . "AcDbEntity") (8 . "LOUVERS") (62 . 7) (370 . 13) (100 . "AcDbLine") (10 1321.2895927602
5180.9954751131 0.0) (11 1321.2895927602 4074.07239819 0.0))
((0 . "LINE") (100 . "AcDbEntity") (8 . "LOUVERS") (62 . 7) (370 . 13) (100 . "AcDbLine") (10 2352.9411764706
5180.9954751131 0.0) (11 2402.5452488688 5180.9954751131 0.0))
((0 . "LINE") (100 . "AcDbEntity") (8 . "LOUVERS") (62 . 7) (370 . 13) (100 . "AcDbLine") (10 2402.5452488688
5180.9954751131 0.0) (11 2475.4751131222 5180.9954751131 0.0))
((0 . "LINE") (100 . "AcDbEntity") (8 . "LOUVERS") (62 . 7) (370 . 13) (100 . "AcDbLine") (10 2475.4751131222
5180.9954751131 0.0) (11 2531.0633484163 5180.9954751131 0.0))
((0 . "LINE") (100 . "AcDbEntity") (8 . "LOUVERS") (62 . 7) (370 . 13) (100 . "AcDbLine") (10 2531.0633484163
5180.9954751131 0.0) (11 2567.3755656109 5180.9954751131 0.0))
((0 . "LINE") (100 . "AcDbEntity") (8 . "LOUVERS") (62 . 7) (370 . 13) (100 . "AcDbLine") (10 2567.3755656109
5180.9954751131 0.0) (11 2613.6990950226 5180.9954751131 0.0))
((0 . "LINE") (100 . "AcDbEntity") (8 . "LOUVERS") (62 . 7) (370 . 13) (100 . "AcDbLine") (10 2613.6990950226
5180.9954751131 0.0) (11 2635.5090497738 5180.9954751131 0.0))
((0 . "LINE") (100 . "AcDbEntity") (8 . "LOUVERS") (62 . 7) (370 . 13) (100 . "AcDbLine") (10 2635.5090497738
5180.9954751131 0.0) (11 2680.9954751131 5180.9954751131 0.0))
((0 . "LINE") (100 . "AcDbEntity") (8 . "LOUVERS") (62 . 7) (370 . 13) (100 . "AcDbLine") (10 2680.9954751131
5180.9954751131 0.0) (11 2680.9954751131 4819.0045248869 0.0))
((0 . "LINE") (100 . "AcDbEntity") (8 . "LOUVERS") (62 . 7) (370 . 13) (100 . "AcDbLine") (10 2680.9954751131
4819.0045248869 0.0) (11 2680.9954751131 4457.0135746606 0.0))
((0 . "LINE") (100 . "AcDbEntity") (8 . "LOUVERS") (62 . 7) (370 . 13) (100 . "AcDbLine") (10 2680.9954751131
4457.0135746606 0.0) (11 2680.9954751131 4095.8927941176 0.0))
((0 . "LINE") (100 . "AcDbEntity") (8 . "LOUVERS") (62 . 7) (370 . 13) (100 . "AcDbLine") (10 2352.9411764706
4120.4751131222 0.0) (11 2352.9411764706 5180.9954751131 0.0))
((0 . "LINE") (100 . "AcDbEntity") (8 . "LOUVERS") (62 . 7) (370 . 13) (100 . "AcDbLine") (10 2402.5452488688
5180.9954751131 0.0) (11 2402.5452488688 4084.9547511312 0.0))
((0 . "LINE") (100 . "AcDbEntity") (8 . "LOUVERS") (62 . 7) (370 . 13) (100 . "AcDbLine") (10 2475.4751131222
5180.9954751131 0.0) (11 2475.4751131222 4105.7918552036 0.0))
((0 . "LINE") (100 . "AcDbEntity") (8 . "LOUVERS") (62 . 7) (370 . 13) (100 . "AcDbLine") (10 2531.0633484163
5180.9954751131 0.0) (11 2531.0633484163 4121.6742081448 0.0))
((0 . "LINE") (100 . "AcDbEntity") (8 . "LOUVERS") (62 . 7) (370 . 13) (100 . "AcDbLine") (10 2567.3755656109
5180.9954751131 0.0) (11 2567.3755656109 4132.0491289593 0.0))
((0 . "LINE") (100 . "AcDbEntity") (8 . "LOUVERS") (62 . 7) (370 . 13) (100 . "AcDbLine") (10 2613.6990950226
5180.9954751131 0.0) (11 2613.6990950226 4145.2844230769 0.0))
((0 . "LINE") (100 . "AcDbEntity") (8 . "LOUVERS") (62 . 7) (370 . 13) (100 . "AcDbLine") (10 2635.5090497738
5180.9954751131 0.0) (11 2635.5090497738 4151.5158371041 0.0))
((0 . "LINE") (100 . "AcDbEntity") (8 . "LOUVERS") (62 . 7) (370 . 13) (100 . "AcDbLine") (10 1018.0995475113
2352.9411764706 0.0) (11 1062.4208144796 2352.9411764706 0.0))
((0 . "LINE") (100 . "AcDbEntity") (8 . "LOUVERS") (62 . 7) (370 . 13) (100 . "AcDbLine") (10 1062.4208144796
2352.9411764706 0.0) (11 1088.6085972851 2352.9411764706 0.0))
((0 . "LINE") (100 . "AcDbEntity") (8 . "LOUVERS") (62 . 7) (370 . 13) (100 . "AcDbLine") (10 1088.6085972851
2352.9411764706 0.0) (11 1132.8280542986 2352.9411764706 0.0))
((0 . "LINE") (100 . "AcDbEntity") (8 . "LOUVERS") (62 . 7) (370 . 13) (100 . "AcDbLine") (10 1132.8280542986
2352.9411764706 0.0) (11 1188.9366515837 2352.9411764706 0.0))
((0 . "LINE") (100 . "AcDbEntity") (8 . "LOUVERS") (62 . 7) (370 . 13) (100 . "AcDbLine") (10 1188.9366515837
2352.9411764706 0.0) (11 1207.1606334842 2352.9411764706 0.0))
((0 . "LINE") (100 . "AcDbEntity") (8 . "LOUVERS") (62 . 7) (370 . 13) (100 . "AcDbLine") (10 1207.1606334842
2352.9411764706 0.0) (11 1251.4027149321 2352.9411764706 0.0))
((0 . "LINE") (100 . "AcDbEntity") (8 . "LOUVERS") (62 . 7) (370 . 13) (100 . "AcDbLine") (10 1251.4027149321
2352.9411764706 0.0) (11 1302.9411764706 2352.9411764706 0.0))
((0 . "LINE") (100 . "AcDbEntity") (8 . "LOUVERS") (62 . 7) (370 . 13) (100 . "AcDbLine") (10 1302.9411764706
2352.9411764706 0.0) (11 1320.6447963801 2352.9411764706 0.0))
((0 . "LINE") (100 . "AcDbEntity") (8 . "LOUVERS") (62 . 7) (370 . 13) (100 . "AcDbLine") (10 1320.6447963801
2352.9411764706 0.0) (11 1334.8416289593 2352.9411764706 0.0))
((0 . "LINE") (100 . "AcDbEntity") (8 . "LOUVERS") (62 . 7) (370 . 13) (100 . "AcDbLine") (10 1334.8416289593
2352.9411764706 0.0) (11 1334.8416289593 1250.2976923077 0.0))
((0 . "LINE") (100 . "AcDbEntity") (8 . "LOUVERS") (62 . 7) (370 . 13) (100 . "AcDbLine") (10 1018.0995475113
1319.1785633484 0.0) (11 1018.0995475113 1651.5837104072 0.0))
((0 . "LINE") (100 . "AcDbEntity") (8 . "LOUVERS") (62 . 7) (370 . 13) (100 . "AcDbLine") (10 1018.0995475113
1651.5837104072 0.0) (11 1018.0995475113 2047.5113122172 0.0))
((0 . "LINE") (100 . "AcDbEntity") (8 . "LOUVERS") (62 . 7) (370 . 13) (100 . "AcDbLine") (10 1018.0995475113
2047.5113122172 0.0) (11 1018.0995475113 2352.9411764706 0.0))
((0 . "LINE") (100 . "AcDbEntity") (8 . "LOUVERS") (62 . 7) (370 . 13) (100 . "AcDbLine") (10 1062.4208144796
2352.9411764706 0.0) (11 1062.4208144796 1353.2718438914 0.0))
((0 . "LINE") (100 . "AcDbEntity") (8 . "LOUVERS") (62 . 7) (370 . 13) (100 . "AcDbLine") (10 1088.6085972851
2352.9411764706 0.0) (11 1088.6085972851 1373.4162895928 0.0))
((0 . "LINE") (100 . "AcDbEntity") (8 . "LOUVERS") (62 . 7) (370 . 13) (100 . "AcDbLine") (10 1132.8280542986
2352.9411764706 0.0) (11 1132.8280542986 1341.813438914 0.0))
((0 . "LINE") (100 . "AcDbEntity") (8 . "LOUVERS") (62 . 7) (370 . 13) (100 . "AcDbLine") (10 1188.9366515837
2352.9411764706 0.0) (11 1188.9366515837 1281.3887895928 0.0))
((0 . "LINE") (100 . "AcDbEntity") (8 . "LOUVERS") (62 . 7) (370 . 13) (100 . "AcDbLine") (10 1207.1606334842
2352.9411764706 0.0) (11 1207.1606334842 1261.7629638009 0.0))
((0 . "LINE") (100 . "AcDbEntity") (8 . "LOUVERS") (62 . 7) (370 . 13) (100 . "AcDbLine") (10 1251.4027149321
2352.9411764706 0.0) (11 1251.4027149321 1223.9485633484 0.0))
((0 . "LINE") (100 . "AcDbEntity") (8 . "LOUVERS") (62 . 7) (370 . 13) (100 . "AcDbLine") (10 1302.9411764706
2352.9411764706 0.0) (11 1302.9411764706 1240.2238574661 0.0))
((0 . "LINE") (100 . "AcDbEntity") (8 . "LOUVERS") (62 . 7) (370 . 13) (100 . "AcDbLine") (10 1320.6447963801
2352.9411764706 0.0) (11 1320.6447963801 1245.814479638 0.0))
((0 . "LINE") (100 . "AcDbEntity") (8 . "LOUVERS") (62 . 7) (370 . 13) (100 . "AcDbLine") (10 2352.9411764706
2352.9411764706 0.0) (11 2402.7601809955 2352.9411764706 0.0))
((0 . "LINE") (100 . "AcDbEntity") (8 . "LOUVERS") (62 . 7) (370 . 13) (100 . "AcDbLine") (10 2402.7601809955
2352.9411764706 0.0) (11 2420.9049773756 2352.9411764706 0.0))
((0 . "LINE") (100 . "AcDbEntity") (8 . "LOUVERS") (62 . 7) (370 . 13) (100 . "AcDbLine") (10 2420.9049773756
2352.9411764706 0.0) (11 2475.0113122172 2352.9411764706 0.0))
((0 . "LINE") (100 . "AcDbEntity") (8 . "LOUVERS") (62 . 7) (370 . 13) (100 . "AcDbLine") (10 2475.0113122172
2352.9411764706 0.0) (11 2528.9592760181 2352.9411764706 0.0))
((0 . "LINE") (100 . "AcDbEntity") (8 . "LOUVERS") (62 . 7) (370 . 13) (100 . "AcDbLine") (10 2528.9592760181
2352.9411764706 0.0) (11 2567.6018099548 2352.9411764706 0.0))
((0 . "LINE") (100 . "AcDbEntity") (8 . "LOUVERS") (62 . 7) (370 . 13) (100 . "AcDbLine") (10 2567.6018099548
2352.9411764706 0.0) (11 2613.2918552036 2352.9411764706 0.0))
((0 . "LINE") (100 . "AcDbEntity") (8 . "LOUVERS") (62 . 7) (370 . 13) (100 . "AcDbLine") (10 2613.2918552036
2352.9411764706 0.0) (11 2635.2488687783 2352.9411764706 0.0))
((0 . "LINE") (100 . "AcDbEntity") (8 . "LOUVERS") (62 . 7) (370 . 13) (100 . "AcDbLine") (10 2635.2488687783
2352.9411764706 0.0) (11 2680.9954751131 2352.9411764706 0.0))
((0 . "LINE") (100 . "AcDbEntity") (8 . "LOUVERS") (62 . 7) (370 . 13) (100 . "AcDbLine") (10 2680.9954751131
2352.9411764706 0.0) (11 2680.9954751131 2047.5113122172 0.0))
((0 . "LINE") (100 . "AcDbEntity") (8 . "LOUVERS") (62 . 7) (370 . 13) (100 . "AcDbLine") (10 2680.9954751131
2047.5113122172 0.0) (11 2680.9954751131 1651.5837104072 0.0))
((0 . "LINE") (100 . "AcDbEntity") (8 . "LOUVERS") (62 . 7) (370 . 13) (100 . "AcDbLine") (10 2680.9954751131
1651.5837104072 0.0) (11 2680.9954751131 1267.8384954751 0.0))
((0 . "LINE") (100 . "AcDbEntity") (8 . "LOUVERS") (62 . 7) (370 . 13) (100 . "AcDbLine") (10 2352.9411764706
1292.4208144796 0.0) (11 2352.9411764706 2352.9411764706 0.0))
((0 . "LINE") (100 . "AcDbEntity") (8 . "LOUVERS") (62 . 7) (370 . 13) (100 . "AcDbLine") (10 2402.7601809955
2352.9411764706 0.0) (11 2402.7601809955 1256.9618665158 0.0))
((0 . "LINE") (100 . "AcDbEntity") (8 . "LOUVERS") (62 . 7) (370 . 13) (100 . "AcDbLine") (10 2420.9049773756
2352.9411764706 0.0) (11 2420.9049773756 1262.1460859729 0.0))
((0 . "LINE") (100 . "AcDbEntity") (8 . "LOUVERS") (62 . 7) (370 . 13) (100 . "AcDbLine") (10 2475.0113122172
2352.9411764706 0.0) (11 2475.0113122172 1277.6050452489 0.0))
((0 . "LINE") (100 . "AcDbEntity") (8 . "LOUVERS") (62 . 7) (370 . 13) (100 . "AcDbLine") (10 2528.9592760181
2352.9411764706 0.0) (11 2528.9592760181 1293.0187443439 0.0))
((0 . "LINE") (100 . "AcDbEntity") (8 . "LOUVERS") (62 . 7) (370 . 13) (100 . "AcDbLine") (10 2567.6018099548
2352.9411764706 0.0) (11 2567.6018099548 1304.0594683258 0.0))
((0 . "LINE") (100 . "AcDbEntity") (8 . "LOUVERS") (62 . 7) (370 . 13) (100 . "AcDbLine") (10 2613.2918552036
2352.9411764706 0.0) (11 2613.2918552036 1317.1137669683 0.0))
((0 . "LINE") (100 . "AcDbEntity") (8 . "LOUVERS") (62 . 7) (370 . 13) (100 . "AcDbLine") (10 2635.2488687783
2352.9411764706 0.0) (11 2635.2488687783 1323.3872058824 0.0))
((0 . "LINE") (100 . "AcDbEntity") (8 . "LOUVERS") (62 . 7) (370 . 13) (100 . "AcDbLine") (10 17352.9411764706
5180.9954751131 0.0) (11 17376.0746606335 5180.9954751131 0.0))
((0 . "LINE") (100 . "AcDbEntity") (8 . "LOUVERS") (62 . 7) (370 . 13) (100 . "AcDbLine") (10 17376.0746606335
5180.9954751131 0.0) (11 17399.185520362 5180.9954751131 0.0))
((0 . "LINE") (100 . "AcDbEntity") (8 . "LOUVERS") (62 . 7) (370 . 13) (100 . "AcDbLine") (10 17399.185520362
5180.9954751131 0.0) (11 17445.463800905 5180.9954751131 0.0))
((0 . "LINE") (100 . "AcDbEntity") (8 . "LOUVERS") (62 . 7) (370 . 13) (100 . "AcDbLine") (10 17445.463800905
5180.9954751131 0.0) (11 17508.0882352941 5180.9954751131 0.0))
((0 . "LINE") (100 . "AcDbEntity") (8 . "LOUVERS") (62 . 7) (370 . 13) (100 . "AcDbLine") (10 17508.0882352941
5180.9954751131 0.0) (11 17554.8076923077 5180.9954751131 0.0))
((0 . "LINE") (100 . "AcDbEntity") (8 . "LOUVERS") (62 . 7) (370 . 13) (100 . "AcDbLine") (10 17554.8076923077
5180.9954751131 0.0) (11 17604.8416289593 5180.9954751131 0.0))
((0 . "LINE") (100 . "AcDbEntity") (8 . "LOUVERS") (62 . 7) (370 . 13) (100 . "AcDbLine") (10 17604.8416289593
5180.9954751131 0.0) (11 17669.6832579186 5180.9954751131 0.0))
((0 . "LINE") (100 . "AcDbEntity") (8 . "LOUVERS") (62 . 7) (370 . 13) (100 . "AcDbLine") (10 17669.6832579186
5180.9954751131 0.0) (11 17669.6832579186 4173.3379751131 0.0))
((0 . "LINE") (100 . "AcDbEntity") (8 . "LOUVERS") (62 . 7) (370 . 13) (100 . "AcDbLine") (10 17352.9411764706
4015.8371040724 0.0) (11 17352.9411764706 4457.0135746606 0.0))
((0 . "LINE") (100 . "AcDbEntity") (8 . "LOUVERS") (62 . 7) (370 . 13) (100 . "AcDbLine") (10 17352.9411764706
4457.0135746606 0.0) (11 17352.9411764706 4819.0045248869 0.0))
((0 . "LINE") (100 . "AcDbEntity") (8 . "LOUVERS") (62 . 7) (370 . 13) (100 . "AcDbLine") (10 17352.9411764706
4819.0045248869 0.0) (11 17352.9411764706 5180.9954751131 0.0))
((0 . "LINE") (100 . "AcDbEntity") (8 . "LOUVERS") (62 . 7) (370 . 13) (100 . "AcDbLine") (10 17376.0746606335
5180.9954751131 0.0) (11 17376.0746606335 4041.7452262443 0.0))
((0 . "LINE") (100 . "AcDbEntity") (8 . "LOUVERS") (62 . 7) (370 . 13) (100 . "AcDbLine") (10 17399.185520362
5180.9954751131 0.0) (11 17399.185520362 4048.1649095023 0.0))
((0 . "LINE") (100 . "AcDbEntity") (8 . "LOUVERS") (62 . 7) (370 . 13) (100 . "AcDbLine") (10 17445.463800905
5180.9954751131 0.0) (11 17445.463800905 4061.0199886878 0.0))
((0 . "LINE") (100 . "AcDbEntity") (8 . "LOUVERS") (62 . 7) (370 . 13) (100 . "AcDbLine") (10 17508.0882352941
5180.9954751131 0.0) (11 17508.0882352941 4078.4156561086 0.0))
((0 . "LINE") (100 . "AcDbEntity") (8 . "LOUVERS") (62 . 7) (370 . 13) (100 . "AcDbLine") (10 17554.8076923077
5180.9954751131 0.0) (11 17554.8076923077 4091.3932918552 0.0))
((0 . "LINE") (100 . "AcDbEntity") (8 . "LOUVERS") (62 . 7) (370 . 13) (100 . "AcDbLine") (10 17604.8416289593
5180.9954751131 0.0) (11 17604.8416289593 4123.4597963801 0.0))
((0 . "LINE") (100 . "AcDbEntity") (8 . "LOUVERS") (62 . 7) (370 . 13) (100 . "AcDbLine") (10 18687.7828054299
5180.9954751131 0.0) (11 18761.57239819 5180.9954751131 0.0))
((0 . "LINE") (100 . "AcDbEntity") (8 . "LOUVERS") (62 . 7) (370 . 13) (100 . "AcDbLine") (10 18761.57239819
5180.9954751131 0.0) (11 18806.0859728507 5180.9954751131 0.0))
((0 . "LINE") (100 . "AcDbEntity") (8 . "LOUVERS") (62 . 7) (370 . 13) (100 . "AcDbLine") (10 18806.0859728507
5180.9954751131 0.0) (11 18862.6131221719 5180.9954751131 0.0))
((0 . "LINE") (100 . "AcDbEntity") (8 . "LOUVERS") (62 . 7) (370 . 13) (100 . "AcDbLine") (10 18862.6131221719
5180.9954751131 0.0) (11 18904.4457013575 5180.9954751131 0.0))
((0 . "LINE") (100 . "AcDbEntity") (8 . "LOUVERS") (62 . 7) (370 . 13) (100 . "AcDbLine") (10 18904.4457013575
5180.9954751131 0.0) (11 18923.5633484163 5180.9954751131 0.0))
((0 . "LINE") (100 . "AcDbEntity") (8 . "LOUVERS") (62 . 7) (370 . 13) (100 . "AcDbLine") (10 18923.5633484163
5180.9954751131 0.0) (11 18962.5226244344 5180.9954751131 0.0))
((0 . "LINE") (100 . "AcDbEntity") (8 . "LOUVERS") (62 . 7) (370 . 13) (100 . "AcDbLine") (10 18962.5226244344
5180.9954751131 0.0) (11 18980.3733031674 5180.9954751131 0.0))
((0 . "LINE") (100 . "AcDbEntity") (8 . "LOUVERS") (62 . 7) (370 . 13) (100 . "AcDbLine") (10 18980.3733031674
5180.9954751131 0.0) (11 19015.8371040724 5180.9954751131 0.0))
((0 . "LINE") (100 . "AcDbEntity") (8 . "LOUVERS") (62 . 7) (370 . 13) (100 . "AcDbLine") (10 19015.8371040724
5180.9954751131 0.0) (11 19015.8371040724 4819.0045248869 0.0))
((0 . "LINE") (100 . "AcDbEntity") (8 . "LOUVERS") (62 . 7) (370 . 13) (100 . "AcDbLine") (10 19015.8371040724
4819.0045248869 0.0) (11 19015.8371040724 4457.0135746606 0.0))
((0 . "LINE") (100 . "AcDbEntity") (8 . "LOUVERS") (62 . 7) (370 . 13) (100 . "AcDbLine") (10 19015.8371040724
4457.0135746606 0.0) (11 19015.8371040724 4083.7104072398 0.0))
((0 . "LINE") (100 . "AcDbEntity") (8 . "LOUVERS") (62 . 7) (370 . 13) (100 . "AcDbLine") (10 18687.7828054299
4062.7020022624 0.0) (11 18687.7828054299 5180.9954751131 0.0))
((0 . "LINE") (100 . "AcDbEntity") (8 . "LOUVERS") (62 . 7) (370 . 13) (100 . "AcDbLine") (10 18761.57239819
5180.9954751131 0.0) (11 18761.57239819 4147.0329638009 0.0))
((0 . "LINE") (100 . "AcDbEntity") (8 . "LOUVERS") (62 . 7) (370 . 13) (100 . "AcDbLine") (10 18806.0859728507
5180.9954751131 0.0) (11 18806.0859728507 4197.9056221719 0.0))
((0 . "LINE") (100 . "AcDbEntity") (8 . "LOUVERS") (62 . 7) (370 . 13) (100 . "AcDbLine") (10 18862.6131221719
5180.9954751131 0.0) (11 18862.6131221719 4208.20489819 0.0))
((0 . "LINE") (100 . "AcDbEntity") (8 . "LOUVERS") (62 . 7) (370 . 13) (100 . "AcDbLine") (10 18904.4457013575
5180.9954751131 0.0) (11 18904.4457013575 4174.2159162896 0.0))
((0 . "LINE") (100 . "AcDbEntity") (8 . "LOUVERS") (62 . 7) (370 . 13) (100 . "AcDbLine") (10 18923.5633484163
5180.9954751131 0.0) (11 18923.5633484163 4158.6828280543 0.0))
((0 . "LINE") (100 . "AcDbEntity") (8 . "LOUVERS") (62 . 7) (370 . 13) (100 . "AcDbLine") (10 18962.5226244344
5180.9954751131 0.0) (11 18962.5226244344 4127.0284162896 0.0))
((0 . "LINE") (100 . "AcDbEntity") (8 . "LOUVERS") (62 . 7) (370 . 13) (100 . "AcDbLine") (10 18980.3733031674
5180.9954751131 0.0) (11 18980.3733031674 4112.524739819 0.0))
((0 . "LINE") (100 . "AcDbEntity") (8 . "LOUVERS") (62 . 7) (370 . 13) (100 . "AcDbLine") (10 17352.9411764706
2352.9411764706 0.0) (11 17375.7918552036 2352.9411764706 0.0))
((0 . "LINE") (100 . "AcDbEntity") (8 . "LOUVERS") (62 . 7) (370 . 13) (100 . "AcDbLine") (10 17375.7918552036
2352.9411764706 0.0) (11 17399.3552036199 2352.9411764706 0.0))
((0 . "LINE") (100 . "AcDbEntity") (8 . "LOUVERS") (62 . 7) (370 . 13) (100 . "AcDbLine") (10 17399.3552036199
2352.9411764706 0.0) (11 17445.4185520362 2352.9411764706 0.0))
((0 . "LINE") (100 . "AcDbEntity") (8 . "LOUVERS") (62 . 7) (370 . 13) (100 . "AcDbLine") (10 17445.4185520362
2352.9411764706 0.0) (11 17507.1153846154 2352.9411764706 0.0))
((0 . "LINE") (100 . "AcDbEntity") (8 . "LOUVERS") (62 . 7) (370 . 13) (100 . "AcDbLine") (10 17507.1153846154
2352.9411764706 0.0) (11 17554.8642533937 2352.9411764706 0.0))
((0 . "LINE") (100 . "AcDbEntity") (8 . "LOUVERS") (62 . 7) (370 . 13) (100 . "AcDbLine") (10 17554.8642533937
2352.9411764706 0.0) (11 17606.0859728507 2352.9411764706 0.0))
((0 . "LINE") (100 . "AcDbEntity") (8 . "LOUVERS") (62 . 7) (370 . 13) (100 . "AcDbLine") (10 17606.0859728507
2352.9411764706 0.0) (11 17669.6832579186 2352.9411764706 0.0))
((0 . "LINE") (100 . "AcDbEntity") (8 . "LOUVERS") (62 . 7) (370 . 13) (100 . "AcDbLine") (10 17669.6832579186
2352.9411764706 0.0) (11 17669.6832579186 1345.2836764706 0.0))
((0 . "LINE") (100 . "AcDbEntity") (8 . "LOUVERS") (62 . 7) (370 . 13) (100 . "AcDbLine") (10 17352.9411764706
1187.7828054299 0.0) (11 17352.9411764706 1651.5837104072 0.0))
((0 . "LINE") (100 . "AcDbEntity") (8 . "LOUVERS") (62 . 7) (370 . 13) (100 . "AcDbLine") (10 17352.9411764706
1651.5837104072 0.0) (11 17352.9411764706 2047.5113122172 0.0))
((0 . "LINE") (100 . "AcDbEntity") (8 . "LOUVERS") (62 . 7) (370 . 13) (100 . "AcDbLine") (10 17352.9411764706
2047.5113122172 0.0) (11 17352.9411764706 2352.9411764706 0.0))
((0 . "LINE") (100 . "AcDbEntity") (8 . "LOUVERS") (62 . 7) (370 . 13) (100 . "AcDbLine") (10 17375.7918552036
2352.9411764706 0.0) (11 17375.7918552036 1213.6123642534 0.0))
((0 . "LINE") (100 . "AcDbEntity") (8 . "LOUVERS") (62 . 7) (370 . 13) (100 . "AcDbLine") (10 17399.3552036199
2352.9411764706 0.0) (11 17399.3552036199 1220.1577375566 0.0))
((0 . "LINE") (100 . "AcDbEntity") (8 . "LOUVERS") (62 . 7) (370 . 13) (100 . "AcDbLine") (10 17445.4185520362
2352.9411764706 0.0) (11 17445.4185520362 1232.9531221719 0.0))
((0 . "LINE") (100 . "AcDbEntity") (8 . "LOUVERS") (62 . 7) (370 . 13) (100 . "AcDbLine") (10 17507.1153846154
2352.9411764706 0.0) (11 17507.1153846154 1250.0911312217 0.0))
((0 . "LINE") (100 . "AcDbEntity") (8 . "LOUVERS") (62 . 7) (370 . 13) (100 . "AcDbLine") (10 17554.8642533937
2352.9411764706 0.0) (11 17554.8642533937 1263.3547058824 0.0))
((0 . "LINE") (100 . "AcDbEntity") (8 . "LOUVERS") (62 . 7) (370 . 13) (100 . "AcDbLine") (10 17606.0859728507
2352.9411764706 0.0) (11 17606.0859728507 1296.3626923077 0.0))
((0 . "LINE") (100 . "AcDbEntity") (8 . "LOUVERS") (62 . 7) (370 . 13) (100 . "AcDbLine") (10 18687.7828054299
2352.9411764706 0.0) (11 18696.9796380091 2352.9411764706 0.0))
((0 . "LINE") (100 . "AcDbEntity") (8 . "LOUVERS") (62 . 7) (370 . 13) (100 . "AcDbLine") (10 18696.9796380091
2352.9411764706 0.0) (11 18762.3190045249 2352.9411764706 0.0))
((0 . "LINE") (100 . "AcDbEntity") (8 . "LOUVERS") (62 . 7) (370 . 13) (100 . "AcDbLine") (10 18762.3190045249
2352.9411764706 0.0) (11 18805.056561086 2352.9411764706 0.0))
((0 . "LINE") (100 . "AcDbEntity") (8 . "LOUVERS") (62 . 7) (370 . 13) (100 . "AcDbLine") (10 18805.056561086
2352.9411764706 0.0) (11 18818.9027149321 2352.9411764706 0.0))
((0 . "LINE") (100 . "AcDbEntity") (8 . "LOUVERS") (62 . 7) (370 . 13) (100 . "AcDbLine") (10 18818.9027149321
2352.9411764706 0.0) (11 18859.4230769231 2352.9411764706 0.0))
((0 . "LINE") (100 . "AcDbEntity") (8 . "LOUVERS") (62 . 7) (370 . 13) (100 . "AcDbLine") (10 18859.4230769231
2352.9411764706 0.0) (11 18894.0837104072 2352.9411764706 0.0))
((0 . "LINE") (100 . "AcDbEntity") (8 . "LOUVERS") (62 . 7) (370 . 13) (100 . "AcDbLine") (10 18894.0837104072
2352.9411764706 0.0) (11 18923.1674208145 2352.9411764706 0.0))
((0 . "LINE") (100 . "AcDbEntity") (8 . "LOUVERS") (62 . 7) (370 . 13) (100 . "AcDbLine") (10 18923.1674208145
2352.9411764706 0.0) (11 18962.6696832579 2352.9411764706 0.0))
((0 . "LINE") (100 . "AcDbEntity") (8 . "LOUVERS") (62 . 7) (370 . 13) (100 . "AcDbLine") (10 18962.6696832579
2352.9411764706 0.0) (11 18980.2828054299 2352.9411764706 0.0))
((0 . "LINE") (100 . "AcDbEntity") (8 . "LOUVERS") (62 . 7) (370 . 13) (100 . "AcDbLine") (10 18980.2828054299
2352.9411764706 0.0) (11 19015.8371040724 2352.9411764706 0.0))
((0 . "LINE") (100 . "AcDbEntity") (8 . "LOUVERS") (62 . 7) (370 . 13) (100 . "AcDbLine") (10 19015.8371040724
2352.9411764706 0.0) (11 19015.8371040724 2047.5113122172 0.0))
((0 . "LINE") (100 . "AcDbEntity") (8 . "LOUVERS") (62 . 7) (370 . 13) (100 . "AcDbLine") (10 19015.8371040724
2047.5113122172 0.0) (11 19015.8371040724 1651.5837104072 0.0))
((0 . "LINE") (100 . "AcDbEntity") (8 . "LOUVERS") (62 . 7) (370 . 13) (100 . "AcDbLine") (10 19015.8371040724
1651.5837104072 0.0) (11 19015.8371040724 1255.6561085973 0.0))
((0 . "LINE") (100 . "AcDbEntity") (8 . "LOUVERS") (62 . 7) (370 . 13) (100 . "AcDbLine") (10 18687.7828054299
1234.6477036199 0.0) (11 18687.7828054299 2352.9411764706 0.0))
((0 . "LINE") (100 . "AcDbEntity") (8 . "LOUVERS") (62 . 7) (370 . 13) (100 . "AcDbLine") (10 18696.9796380091
2352.9411764706 0.0) (11 18696.9796380091 1245.1583710407 0.0))
((0 . "LINE") (100 . "AcDbEntity") (8 . "LOUVERS") (62 . 7) (370 . 13) (100 . "AcDbLine") (10 18762.3190045249
2352.9411764706 0.0) (11 18762.3190045249 1319.8319343891 0.0))
((0 . "LINE") (100 . "AcDbEntity") (8 . "LOUVERS") (62 . 7) (370 . 13) (100 . "AcDbLine") (10 18805.056561086
2352.9411764706 0.0) (11 18805.056561086 1368.6748529412 0.0))
((0 . "LINE") (100 . "AcDbEntity") (8 . "LOUVERS") (62 . 7) (370 . 13) (100 . "AcDbLine") (10 18818.9027149321
2352.9411764706 0.0) (11 18818.9027149321 1384.4990271493 0.0))
((0 . "LINE") (100 . "AcDbEntity") (8 . "LOUVERS") (62 . 7) (370 . 13) (100 . "AcDbLine") (10 18859.4230769231
2352.9411764706 0.0) (11 18859.4230769231 1382.7425 0.0))
((0 . "LINE") (100 . "AcDbEntity") (8 . "LOUVERS") (62 . 7) (370 . 13) (100 . "AcDbLine") (10 18894.0837104072
2352.9411764706 0.0) (11 18894.0837104072 1354.5807352941 0.0))
((0 . "LINE") (100 . "AcDbEntity") (8 . "LOUVERS") (62 . 7) (370 . 13) (100 . "AcDbLine") (10 18923.1674208145
2352.9411764706 0.0) (11 18923.1674208145 1330.9502262443 0.0))
((0 . "LINE") (100 . "AcDbEntity") (8 . "LOUVERS") (62 . 7) (370 . 13) (100 . "AcDbLine") (10 18962.6696832579
2352.9411764706 0.0) (11 18962.6696832579 1298.8546380091 0.0))
((0 . "LINE") (100 . "AcDbEntity") (8 . "LOUVERS") (62 . 7) (370 . 13) (100 . "AcDbLine") (10 18980.2828054299
2352.9411764706 0.0) (11 18980.2828054299 1284.5439705882 0.0))
((0 . "LINE") (100 . "AcDbEntity") (8 . "GLASS") (62 . 7) (370 . 13) (100 . "AcDbLine") (10 9242.0814479638
7024.8868778281 0.0) (11 9536.1990950226 7375.5656108597 0.0))
((0 . "LINE") (100 . "AcDbEntity") (8 . "GLASS") (62 . 7) (370 . 13) (100 . "AcDbLine") (10 9253.3936651584
6979.6380090498 0.0) (11 9536.1990950226 7296.3800904977 0.0))
((0 . "LINE") (100 . "AcDbEntity") (8 . "GLASS") (62 . 7) (370 . 13) (100 . "AcDbLine") (10 10610.8597285068
7024.8868778281 0.0) (11 10814.4796380091 7375.5656108597 0.0))
((0 . "LINE") (100 . "AcDbEntity") (8 . "GLASS") (62 . 7) (370 . 13) (100 . "AcDbLine") (10 10622.1719457014
6979.6380090498 0.0) (11 10814.4796380091 7296.3800904977 0.0))
((0 . "LINE") (100 . "AcDbEntity") (8 . "GLASS") (62 . 7) (370 . 13) (100 . "AcDbLine") (10 1572.3981900452
4615.3846153846 0.0) (11 1719.4570135747 4819.0045248869 0.0))
((0 . "LINE") (100 . "AcDbEntity") (8 . "GLASS") (62 . 7) (370 . 13) (100 . "AcDbLine") (10 1549.7737556561
4321.2669683258 0.0) (11 1719.4570135747 4581.4479638009 0.0))
((0 . "LINE") (100 . "AcDbEntity") (8 . "GLASS") (62 . 7) (370 . 13) (100 . "AcDbLine") (10 2002.2624434389
4536.1990950226 0.0) (11 2149.3212669683 4762.443438914 0.0))
((0 . "LINE") (100 . "AcDbEntity") (8 . "GLASS") (62 . 7) (370 . 13) (100 . "AcDbLine") (10 1957.0135746606
4309.9547511312 0.0) (11 2149.3212669683 4570.1357466063 0.0))
((0 . "LINE") (100 . "AcDbEntity") (8 . "GLASS") (62 . 7) (370 . 13) (100 . "AcDbLine") (10 5045.2488687783
4457.0135746606 0.0) (11 5248.8687782805 4705.8823529412 0.0))
((0 . "LINE") (100 . "AcDbEntity") (8 . "GLASS") (62 . 7) (370 . 13) (100 . "AcDbLine") (10 4966.0633484163
4162.8959276018 0.0) (11 5248.8687782805 4490.9502262443 0.0))
((0 . "LINE") (100 . "AcDbEntity") (8 . "GLASS") (62 . 7) (370 . 13) (100 . "AcDbLine") (10 5780.5429864253
4445.7013574661 0.0) (11 5972.850678733 4694.5701357466 0.0))
((0 . "LINE") (100 . "AcDbEntity") (8 . "GLASS") (62 . 7) (370 . 13) (100 . "AcDbLine") (10 5701.3574660633
4151.5837104072 0.0) (11 5972.850678733 4479.6380090498 0.0))
((0 . "LINE") (100 . "AcDbEntity") (8 . "GLASS") (62 . 7) (370 . 13) (100 . "AcDbLine") (10 8461.5384615385
4705.8823529412 0.0) (11 8597.2850678733 4909.5022624434 0.0))
((0 . "LINE") (100 . "AcDbEntity") (8 . "GLASS") (62 . 7) (370 . 13) (100 . "AcDbLine") (10 8472.850678733
4570.1357466063 0.0) (11 8631.221719457 4785.0678733032 0.0))
((0 . "LINE") (100 . "AcDbEntity") (8 . "GLASS") (62 . 7) (370 . 13) (100 . "AcDbLine") (10 8880.0904977376
4683.257918552 0.0) (11 9038.4615384615 4898.1900452489 0.0))
((0 . "LINE") (100 . "AcDbEntity") (8 . "GLASS") (62 . 7) (370 . 13) (100 . "AcDbLine") (10 8891.4027149321
4547.5113122172 0.0) (11 9061.0859728507 4762.443438914 0.0))
((0 . "LINE") (100 . "AcDbEntity") (8 . "GLASS") (62 . 7) (370 . 13) (100 . "AcDbLine") (10 8665.1583710407
3642.5339366516 0.0) (11 8959.2760180995 4004.5248868778 0.0))
((0 . "LINE") (100 . "AcDbEntity") (8 . "GLASS") (62 . 7) (370 . 13) (100 . "AcDbLine") (10 8563.3484162896
3404.9773755656 0.0) (11 8925.3393665158 3834.8416289593 0.0))
((0 . "LINE") (100 . "AcDbEntity") (8 . "GLASS") (62 . 7) (370 . 13) (100 . "AcDbLine") (10 10961.5384615385
4705.8823529412 0.0) (11 11108.5972850679 4909.5022624434 0.0))
((0 . "LINE") (100 . "AcDbEntity") (8 . "GLASS") (62 . 7) (370 . 13) (100 . "AcDbLine") (10 10961.5384615385
4570.1357466063 0.0) (11 11153.8461538462 4785.0678733032 0.0))
((0 . "LINE") (100 . "AcDbEntity") (8 . "GLASS") (62 . 7) (370 . 13) (100 . "AcDbLine") (10 11391.4027149321
4671.9457013575 0.0) (11 11527.149321267 4886.8778280543 0.0))
((0 . "LINE") (100 . "AcDbEntity") (8 . "GLASS") (62 . 7) (370 . 13) (100 . "AcDbLine") (10 11368.778280543
4536.1990950226 0.0) (11 11549.7737556561 4751.1312217195 0.0))
((0 . "LINE") (100 . "AcDbEntity") (8 . "GLASS") (62 . 7) (370 . 13) (100 . "AcDbLine") (10 11165.1583710407
3631.221719457 0.0) (11 11470.5882352941 4004.5248868778 0.0))
((0 . "LINE") (100 . "AcDbEntity") (8 . "GLASS") (62 . 7) (370 . 13) (100 . "AcDbLine") (10 11074.6606334842
3393.665158371 0.0) (11 11436.6515837104 3834.8416289593 0.0))
((0 . "LINE") (100 . "AcDbEntity") (8 . "GLASS") (62 . 7) (370 . 13) (100 . "AcDbLine") (10 8348.4162895928
1504.5248868778 0.0) (11 8597.2850678733 1877.8280542986 0.0))
((0 . "LINE") (100 . "AcDbEntity") (8 . "GLASS") (62 . 7) (370 . 13) (100 . "AcDbLine") (10 8303.1674208145
1278.2805429864 0.0) (11 8552.036199095 1662.8959276018 0.0))
((0 . "LINE") (100 . "AcDbEntity") (8 . "GLASS") (62 . 7) (370 . 13) (100 . "AcDbLine") (10 8981.9004524887
1436.6515837104 0.0) (11 9196.8325791855 1730.7692307692 0.0))
((0 . "LINE") (100 . "AcDbEntity") (8 . "GLASS") (62 . 7) (370 . 13) (100 . "AcDbLine") (10 8947.963800905
1255.6561085973 0.0) (11 9185.520361991 1583.7104072398 0.0))
((0 . "LINE") (100 . "AcDbEntity") (8 . "GLASS") (62 . 7) (370 . 13) (100 . "AcDbLine") (10 10871.0407239819
1515.8371040724 0.0) (11 11074.6606334842 1821.2669683258 0.0))
((0 . "LINE") (100 . "AcDbEntity") (8 . "GLASS") (62 . 7) (370 . 13) (100 . "AcDbLine") (10 10825.7918552036
1278.2805429864 0.0) (11 11063.3484162896 1628.9592760181 0.0))
((0 . "LINE") (100 . "AcDbEntity") (8 . "GLASS") (62 . 7) (370 . 13) (100 . "AcDbLine") (10 11470.5882352941
1459.2760180995 0.0) (11 11685.520361991 1730.7692307692 0.0))
((0 . "LINE") (100 . "AcDbEntity") (8 . "GLASS") (62 . 7) (370 . 13) (100 . "AcDbLine") (10 11425.3393665158
1266.9683257919 0.0) (11 11674.2081447964 1561.0859728507 0.0))
((0 . "LINE") (100 . "AcDbEntity") (8 . "GLASS") (62 . 7) (370 . 13) (100 . "AcDbLine") (10 5045.2488687783
1651.5837104072 0.0) (11 5260.1809954751 1945.7013574661 0.0))
((0 . "LINE") (100 . "AcDbEntity") (8 . "GLASS") (62 . 7) (370 . 13) (100 . "AcDbLine") (10 4966.0633484163
1357.4660633484 0.0) (11 5237.556561086 1685.520361991 0.0))
((0 . "LINE") (100 . "AcDbEntity") (8 . "GLASS") (62 . 7) (370 . 13) (100 . "AcDbLine") (10 5780.5429864253
1628.9592760181 0.0) (11 6006.7873303167 1934.3891402715 0.0))
((0 . "LINE") (100 . "AcDbEntity") (8 . "GLASS") (62 . 7) (370 . 13) (100 . "AcDbLine") (10 5712.6696832579
1346.1538461538 0.0) (11 5984.1628959276 1674.2081447964 0.0))
((0 . "LINE") (100 . "AcDbEntity") (8 . "GLASS") (62 . 7) (370 . 13) (100 . "AcDbLine") (10 1572.3981900452
1787.3303167421 0.0) (11 1719.4570135747 1990.9502262443 0.0))
((0 . "LINE") (100 . "AcDbEntity") (8 . "GLASS") (62 . 7) (370 . 13) (100 . "AcDbLine") (10 1549.7737556561
1493.2126696833 0.0) (11 1719.4570135747 1753.3936651584 0.0))
((0 . "LINE") (100 . "AcDbEntity") (8 . "GLASS") (62 . 7) (370 . 13) (100 . "AcDbLine") (10 2002.2624434389
1708.1447963801 0.0) (11 2149.3212669683 1934.3891402715 0.0))
((0 . "LINE") (100 . "AcDbEntity") (8 . "GLASS") (62 . 7) (370 . 13) (100 . "AcDbLine") (10 1957.0135746606
1481.9004524887 0.0) (11 2149.3212669683 1742.0814479638 0.0))
((0 . "LINE") (100 . "AcDbEntity") (8 . "GLASS") (62 . 7) (370 . 13) (100 . "AcDbLine") (10 14196.8325791855
4457.0135746606 0.0) (11 14400.4524886878 4705.8823529412 0.0))
((0 . "LINE") (100 . "AcDbEntity") (8 . "GLASS") (62 . 7) (370 . 13) (100 . "AcDbLine") (10 14117.6470588235
4162.8959276018 0.0) (11 14400.4524886878 4490.9502262443 0.0))
((0 . "LINE") (100 . "AcDbEntity") (8 . "GLASS") (62 . 7) (370 . 13) (100 . "AcDbLine") (10 14932.1266968326
4445.7013574661 0.0) (11 15124.4343891403 4694.5701357466 0.0))
((0 . "LINE") (100 . "AcDbEntity") (8 . "GLASS") (62 . 7) (370 . 13) (100 . "AcDbLine") (10 14852.9411764706
4151.5837104072 0.0) (11 15124.4343891403 4479.6380090498 0.0))
((0 . "LINE") (100 . "AcDbEntity") (8 . "GLASS") (62 . 7) (370 . 13) (100 . "AcDbLine") (10 14196.8325791855
1651.5837104072 0.0) (11 14411.7647058824 1945.7013574661 0.0))
((0 . "LINE") (100 . "AcDbEntity") (8 . "GLASS") (62 . 7) (370 . 13) (100 . "AcDbLine") (10 14117.6470588235
1357.4660633484 0.0) (11 14389.1402714932 1685.520361991 0.0))
((0 . "LINE") (100 . "AcDbEntity") (8 . "GLASS") (62 . 7) (370 . 13) (100 . "AcDbLine") (10 14932.1266968326
1628.9592760181 0.0) (11 15158.371040724 1934.3891402715 0.0))
((0 . "LINE") (100 . "AcDbEntity") (8 . "GLASS") (62 . 7) (370 . 13) (100 . "AcDbLine") (10 14864.2533936652
1346.1538461538 0.0) (11 15135.7466063348 1674.2081447964 0.0))
((0 . "LINE") (100 . "AcDbEntity") (8 . "GLASS") (62 . 7) (370 . 13) (100 . "AcDbLine") (10 17907.2398190045
4615.3846153846 0.0) (11 18054.2986425339 4819.0045248869 0.0))
((0 . "LINE") (100 . "AcDbEntity") (8 . "GLASS") (62 . 7) (370 . 13) (100 . "AcDbLine") (10 17907.2398190045
1787.3303167421 0.0) (11 18054.2986425339 1990.9502262443 0.0))
((0 . "LINE") (100 . "AcDbEntity") (8 . "GLASS") (62 . 7) (370 . 13) (100 . "AcDbLine") (10 17884.6153846154
4321.2669683258 0.0) (11 18054.2986425339 4581.4479638009 0.0))
((0 . "LINE") (100 . "AcDbEntity") (8 . "GLASS") (62 . 7) (370 . 13) (100 . "AcDbLine") (10 17884.6153846154
1493.2126696833 0.0) (11 18054.2986425339 1753.3936651584 0.0))
((0 . "LINE") (100 . "AcDbEntity") (8 . "GLASS") (62 . 7) (370 . 13) (100 . "AcDbLine") (10 18337.1040723982
4536.1990950226 0.0) (11 18484.1628959276 4762.443438914 0.0))
((0 . "LINE") (100 . "AcDbEntity") (8 . "GLASS") (62 . 7) (370 . 13) (100 . "AcDbLine") (10 18337.1040723982
1708.1447963801 0.0) (11 18484.1628959276 1934.3891402715 0.0))
((0 . "LINE") (100 . "AcDbEntity") (8 . "GLASS") (62 . 7) (370 . 13) (100 . "AcDbLine") (10 18291.8552036199
4309.9547511312 0.0) (11 18484.1628959276 4570.1357466063 0.0))
((0 . "LINE") (100 . "AcDbEntity") (8 . "GLASS") (62 . 7) (370 . 13) (100 . "AcDbLine") (10 18291.8552036199
1481.9004524887 0.0) (11 18484.1628959276 1742.0814479638 0.0))
((0 . "LINE") (100 . "AcDbEntity") (8 . "WINDOWS") (62 . 7) (370 . 13) (100 . "AcDbLine") (10 4739.8190045249 5000 0.0)
(11 4739.8190045249 4064.0803846154 0.0))
((0 . "LINE") (100 . "AcDbEntity") (8 . "WINDOWS") (62 . 7) (370 . 13) (100 . "AcDbLine") (10 6153.8461538462 5000 0.0)
(11 6153.8461538462 4184.3296040724 0.0))
((0 . "LINE") (100 . "AcDbEntity") (8 . "WINDOWS") (62 . 7) (370 . 13) (100 . "AcDbLine") (10 4785.0678733032
4966.0633484163 0.0) (11 4785.0678733032 4073.3963235294 0.0))
((0 . "LINE") (100 . "AcDbEntity") (8 . "WINDOWS") (62 . 7) (370 . 13) (100 . "AcDbLine") (10 6108.5972850679
4966.0633484163 0.0) (11 6108.5972850679 4146.2252941176 0.0))
((0 . "LINE") (100 . "AcDbEntity") (8 . "WINDOWS") (62 . 7) (370 . 13) (100 . "AcDbLine") (10 5407.2398190045
5101.3436030836 0.0) (11 5407.2398190045 4053.5444909502 0.0))
((0 . "LINE") (100 . "AcDbEntity") (8 . "WINDOWS") (62 . 7) (370 . 13) (100 . "AcDbLine") (10 5486.4253393665
5101.3436030836 0.0) (11 5486.4253393665 4086.5384615385 0.0))
((0 . "LINE") (100 . "AcDbEntity") (8 . "WINDOWS") (62 . 7) (370 . 13) (100 . "AcDbLine") (10 4728.5067873303
2149.3212669683 0.0) (11 4728.5067873303 1146.4686199095 0.0))
((0 . "LINE") (100 . "AcDbEntity") (8 . "WINDOWS") (62 . 7) (370 . 13) (100 . "AcDbLine") (10 6153.8461538462
2149.3212669683 0.0) (11 6153.8461538462 1128.1365723982 0.0))
((0 . "LINE") (100 . "AcDbEntity") (8 . "WINDOWS") (62 . 7) (370 . 13) (100 . "AcDbLine") (10 4773.7556561086
2104.07239819 0.0) (11 4773.7556561086 1160.2400113122 0.0))
((0 . "LINE") (100 . "AcDbEntity") (8 . "WINDOWS") (62 . 7) (370 . 13) (100 . "AcDbLine") (10 6108.5972850679
2104.07239819 0.0) (11 6108.5972850679 1097.2850678733 0.0))
((0 . "LINE") (100 . "AcDbEntity") (8 . "WINDOWS") (62 . 7) (370 . 13) (100 . "AcDbLine") (10 5407.2398190045
2307.2105866853 0.0) (11 5407.2398190045 1182.1266968326 0.0))
((0 . "LINE") (100 . "AcDbEntity") (8 . "WINDOWS") (62 . 7) (370 . 13) (100 . "AcDbLine") (10 5486.4253393665
2306.8357805128 0.0) (11 5486.4253393665 1142.5339366516 0.0))
((0 . "LINE") (100 . "AcDbEntity") (8 . "WINDOWS") (62 . 7) (370 . 13) (100 . "AcDbLine") (10 13891.4027149321 5000 0.0)
(11 13891.4027149321 4064.0803846154 0.0))
((0 . "LINE") (100 . "AcDbEntity") (8 . "WINDOWS") (62 . 7) (370 . 13) (100 . "AcDbLine") (10 15305.4298642534 5000 0.0)
(11 15305.4298642534 4184.3296040724 0.0))
((0 . "LINE") (100 . "AcDbEntity") (8 . "WINDOWS") (62 . 7) (370 . 13) (100 . "AcDbLine") (10 13936.6515837104
4966.0633484163 0.0) (11 13936.6515837104 4073.3963235294 0.0))
((0 . "LINE") (100 . "AcDbEntity") (8 . "WINDOWS") (62 . 7) (370 . 13) (100 . "AcDbLine") (10 15260.1809954751
4966.0633484163 0.0) (11 15260.1809954751 4146.2252941176 0.0))
((0 . "LINE") (100 . "AcDbEntity") (8 . "WINDOWS") (62 . 7) (370 . 13) (100 . "AcDbLine") (10 14558.8235294118
5101.3436030836 0.0) (11 14558.8235294118 4053.5444909502 0.0))
((0 . "LINE") (100 . "AcDbEntity") (8 . "WINDOWS") (62 . 7) (370 . 13) (100 . "AcDbLine") (10 14638.0090497738
5101.3436030836 0.0) (11 14638.0090497738 4086.5384615385 0.0))
((0 . "LINE") (100 . "AcDbEntity") (8 . "WINDOWS") (62 . 7) (370 . 13) (100 . "AcDbLine") (10 13880.0904977376
2149.3212669683 0.0) (11 13880.0904977376 1146.4686199095 0.0))
((0 . "LINE") (100 . "AcDbEntity") (8 . "WINDOWS") (62 . 7) (370 . 13) (100 . "AcDbLine") (10 15305.4298642534
2149.3212669683 0.0) (11 15305.4298642534 1128.1365723982 0.0))
((0 . "LINE") (100 . "AcDbEntity") (8 . "WINDOWS") (62 . 7) (370 . 13) (100 . "AcDbLine") (10 13925.3393665158
2104.07239819 0.0) (11 13925.3393665158 1160.2400113122 0.0))
((0 . "LINE") (100 . "AcDbEntity") (8 . "WINDOWS") (62 . 7) (370 . 13) (100 . "AcDbLine") (10 15260.1809954751
2104.07239819 0.0) (11 15260.1809954751 1097.2850678733 0.0))
((0 . "LINE") (100 . "AcDbEntity") (8 . "WINDOWS") (62 . 7) (370 . 13) (100 . "AcDbLine") (10 14558.8235294118
2307.2105866853 0.0) (11 14558.8235294118 1182.1266968326 0.0))
((0 . "LINE") (100 . "AcDbEntity") (8 . "WINDOWS") (62 . 7) (370 . 13) (100 . "AcDbLine") (10 14638.0090497738
2306.8357805128 0.0) (11 14638.0090497738 1142.5339366516 0.0))
((0 . "LINE") (100 . "AcDbEntity") (8 . "WINDOWS") (62 . 7) (370 . 13) (100 . "AcDbLine") (10 1346.1538461538
5045.2488687783 0.0) (11 1346.1538461538 4081.9242647059 0.0))
((0 . "LINE") (100 . "AcDbEntity") (8 . "WINDOWS") (62 . 7) (370 . 13) (100 . "AcDbLine") (10 2319.0045248869
5045.2488687783 0.0) (11 2319.0045248869 4148.0486425339 0.0))
((0 . "LINE") (100 . "AcDbEntity") (8 . "WINDOWS") (62 . 7) (370 . 13) (100 . "AcDbLine") (10 1414.0271493213
5011.3122171946 0.0) (11 1414.0271493213 4103.3579411765 0.0))
((0 . "LINE") (100 . "AcDbEntity") (8 . "WINDOWS") (62 . 7) (370 . 13) (100 . "AcDbLine") (10 2251.1312217195
5011.3122171946 0.0) (11 2251.1312217195 4203.1957013575 0.0))
((0 . "LINE") (100 . "AcDbEntity") (8 . "WINDOWS") (62 . 7) (370 . 13) (100 . "AcDbLine") (10 1470.5882352941
4966.0633484163 0.0) (11 1470.5882352941 4113.8763235294 0.0))
((0 . "LINE") (100 . "AcDbEntity") (8 . "WINDOWS") (62 . 7) (370 . 13) (100 . "AcDbLine") (10 2194.5701357466
4966.0633484163 0.0) (11 2194.5701357466 4204.9127375566 0.0))
((0 . "LINE") (100 . "AcDbEntity") (8 . "WINDOWS") (62 . 7) (370 . 13) (100 . "AcDbLine") (10 1798.6425339367
5112.011571045 0.0) (11 1798.6425339367 4114.8190045249 0.0))
((0 . "LINE") (100 . "AcDbEntity") (8 . "WINDOWS") (62 . 7) (370 . 13) (100 . "AcDbLine") (10 1866.5158371041
5112.011571045 0.0) (11 1866.5158371041 4165.7239819005 0.0))
((0 . "LINE") (100 . "AcDbEntity") (8 . "WINDOWS") (62 . 7) (370 . 13) (100 . "AcDbLine") (10 1742.0814479638
5441.1764705882 0.0) (11 1923.0769230769 5441.1764705882 0.0))
((0 . "LINE") (100 . "AcDbEntity") (8 . "WINDOWS") (62 . 7) (370 . 13) (100 . "AcDbLine") (10 1923.0769230769
5441.1764705882 0.0) (11 1900.4051368801 5312.703015473 0.0))
((0 . "LINE") (100 . "AcDbEntity") (8 . "WINDOWS") (62 . 7) (370 . 13) (100 . "AcDbLine") (10 1900.4051368801
5312.703015473 0.0) (11 1889.1402714932 5248.8687782805 0.0))
((0 . "LINE") (100 . "AcDbEntity") (8 . "WINDOWS") (62 . 7) (370 . 13) (100 . "AcDbLine") (10 1889.1402714932
5248.8687782805 0.0) (11 1776.0180995475 5248.8687782805 0.0))
((0 . "LINE") (100 . "AcDbEntity") (8 . "WINDOWS") (62 . 7) (370 . 13) (100 . "AcDbLine") (10 1776.0180995475
5248.8687782805 0.0) (11 1764.7532341606 5312.703015473 0.0))
((0 . "LINE") (100 . "AcDbEntity") (8 . "WINDOWS") (62 . 7) (370 . 13) (100 . "AcDbLine") (10 1764.7532341606
5312.703015473 0.0) (11 1742.0814479638 5441.1764705882 0.0))
((0 . "LINE") (100 . "AcDbEntity") (8 . "WINDOWS") (62 . 7) (370 . 13) (100 . "AcDbLine") (10 1346.1538461538
2217.1945701357 0.0) (11 1346.1538461538 1253.8699660633 0.0))
((0 . "LINE") (100 . "AcDbEntity") (8 . "WINDOWS") (62 . 7) (370 . 13) (100 . "AcDbLine") (10 2319.0045248869
2217.1945701357 0.0) (11 2319.0045248869 1319.9943438914 0.0))
((0 . "LINE") (100 . "AcDbEntity") (8 . "WINDOWS") (62 . 7) (370 . 13) (100 . "AcDbLine") (10 1414.0271493213
2183.257918552 0.0) (11 1414.0271493213 1275.3036425339 0.0))
((0 . "LINE") (100 . "AcDbEntity") (8 . "WINDOWS") (62 . 7) (370 . 13) (100 . "AcDbLine") (10 2251.1312217195
2183.257918552 0.0) (11 2251.1312217195 1375.1414027149 0.0))
((0 . "LINE") (100 . "AcDbEntity") (8 . "WINDOWS") (62 . 7) (370 . 13) (100 . "AcDbLine") (10 1470.5882352941
2138.0090497738 0.0) (11 1470.5882352941 1285.8220248869 0.0))
((0 . "LINE") (100 . "AcDbEntity") (8 . "WINDOWS") (62 . 7) (370 . 13) (100 . "AcDbLine") (10 2194.5701357466
2138.0090497738 0.0) (11 2194.5701357466 1376.858438914 0.0))
((0 . "LINE") (100 . "AcDbEntity") (8 . "WINDOWS") (62 . 7) (370 . 13) (100 . "AcDbLine") (10 1798.6425339367
2283.9572724025 0.0) (11 1798.6425339367 1286.7647058824 0.0))
((0 . "LINE") (100 . "AcDbEntity") (8 . "WINDOWS") (62 . 7) (370 . 13) (100 . "AcDbLine") (10 1866.5158371041
2283.9572724025 0.0) (11 1866.5158371041 1337.6696832579 0.0))
((0 . "LINE") (100 . "AcDbEntity") (8 . "WINDOWS") (62 . 7) (370 . 13) (100 . "AcDbLine") (10 1742.0814479638
2613.1221719457 0.0) (11 1923.0769230769 2613.1221719457 0.0))
((0 . "LINE") (100 . "AcDbEntity") (8 . "WINDOWS") (62 . 7) (370 . 13) (100 . "AcDbLine") (10 1923.0769230769
2613.1221719457 0.0) (11 1900.4051368801 2484.6487168304 0.0))
((0 . "LINE") (100 . "AcDbEntity") (8 . "WINDOWS") (62 . 7) (370 . 13) (100 . "AcDbLine") (10 1900.4051368801
2484.6487168304 0.0) (11 1889.1402714932 2420.814479638 0.0))
((0 . "LINE") (100 . "AcDbEntity") (8 . "WINDOWS") (62 . 7) (370 . 13) (100 . "AcDbLine") (10 1889.1402714932
2420.814479638 0.0) (11 1776.0180995475 2420.814479638 0.0))
((0 . "LINE") (100 . "AcDbEntity") (8 . "WINDOWS") (62 . 7) (370 . 13) (100 . "AcDbLine") (10 1776.0180995475
2420.814479638 0.0) (11 1764.7532341606 2484.6487168304 0.0))
((0 . "LINE") (100 . "AcDbEntity") (8 . "WINDOWS") (62 . 7) (370 . 13) (100 . "AcDbLine") (10 1764.7532341606
2484.6487168304 0.0) (11 1742.0814479638 2613.1221719457 0.0))
((0 . "LINE") (100 . "AcDbEntity") (8 . "WINDOWS") (62 . 7) (370 . 13) (100 . "AcDbLine") (10 17680.9954751131
5045.2488687783 0.0) (11 17680.9954751131 4182.0396832579 0.0))
((0 . "LINE") (100 . "AcDbEntity") (8 . "WINDOWS") (62 . 7) (370 . 13) (100 . "AcDbLine") (10 18653.8461538462
5045.2488687783 0.0) (11 18653.8461538462 4065.3280542986 0.0))
((0 . "LINE") (100 . "AcDbEntity") (8 . "WINDOWS") (62 . 7) (370 . 13) (100 . "AcDbLine") (10 17748.8687782805
5011.3122171946 0.0) (11 17748.8687782805 4171.5976357466 0.0))
((0 . "LINE") (100 . "AcDbEntity") (8 . "WINDOWS") (62 . 7) (370 . 13) (100 . "AcDbLine") (10 18585.9728506787
5011.3122171946 0.0) (11 18585.9728506787 4111.9909502262 0.0))
((0 . "LINE") (100 . "AcDbEntity") (8 . "WINDOWS") (62 . 7) (370 . 13) (100 . "AcDbLine") (10 17805.4298642534
4966.0633484163 0.0) (11 17805.4298642534 4110.6856900452 0.0))
((0 . "LINE") (100 . "AcDbEntity") (8 . "WINDOWS") (62 . 7) (370 . 13) (100 . "AcDbLine") (10 18529.4117647059
4966.0633484163 0.0) (11 18529.4117647059 4150.8766968326 0.0))
((0 . "LINE") (100 . "AcDbEntity") (8 . "WINDOWS") (62 . 7) (370 . 13) (100 . "AcDbLine") (10 18133.4841628959
5112.011571045 0.0) (11 18133.4841628959 4098.7933597285 0.0))
((0 . "LINE") (100 . "AcDbEntity") (8 . "WINDOWS") (62 . 7) (370 . 13) (100 . "AcDbLine") (10 18201.3574660633
5112.011571045 0.0) (11 18201.3574660633 4076.1689253394 0.0))
((0 . "LINE") (100 . "AcDbEntity") (8 . "WINDOWS") (62 . 7) (370 . 13) (100 . "AcDbLine") (10 18076.9230769231
5441.1764705882 0.0) (11 18257.9185520362 5441.1764705882 0.0))
((0 . "LINE") (100 . "AcDbEntity") (8 . "WINDOWS") (62 . 7) (370 . 13) (100 . "AcDbLine") (10 18257.9185520362
5441.1764705882 0.0) (11 18235.2467658394 5312.703015473 0.0))
((0 . "LINE") (100 . "AcDbEntity") (8 . "WINDOWS") (62 . 7) (370 . 13) (100 . "AcDbLine") (10 18235.2467658394
5312.703015473 0.0) (11 18223.9819004525 5248.8687782805 0.0))
((0 . "LINE") (100 . "AcDbEntity") (8 . "WINDOWS") (62 . 7) (370 . 13) (100 . "AcDbLine") (10 18223.9819004525
5248.8687782805 0.0) (11 18110.8597285068 5248.8687782805 0.0))
((0 . "LINE") (100 . "AcDbEntity") (8 . "WINDOWS") (62 . 7) (370 . 13) (100 . "AcDbLine") (10 18110.8597285068
5248.8687782805 0.0) (11 18099.5948631199 5312.703015473 0.0))
((0 . "LINE") (100 . "AcDbEntity") (8 . "WINDOWS") (62 . 7) (370 . 13) (100 . "AcDbLine") (10 18099.5948631199
5312.703015473 0.0) (11 18076.9230769231 5441.1764705882 0.0))
((0 . "LINE") (100 . "AcDbEntity") (8 . "WINDOWS") (62 . 7) (370 . 13) (100 . "AcDbLine") (10 17680.9954751131
2217.1945701357 0.0) (11 17680.9954751131 1353.9853846154 0.0))
((0 . "LINE") (100 . "AcDbEntity") (8 . "WINDOWS") (62 . 7) (370 . 13) (100 . "AcDbLine") (10 18653.8461538462
2217.1945701357 0.0) (11 18653.8461538462 1237.2737556561 0.0))
((0 . "LINE") (100 . "AcDbEntity") (8 . "WINDOWS") (62 . 7) (370 . 13) (100 . "AcDbLine") (10 17748.8687782805
2183.257918552 0.0) (11 17748.8687782805 1343.5433371041 0.0))
((0 . "LINE") (100 . "AcDbEntity") (8 . "WINDOWS") (62 . 7) (370 . 13) (100 . "AcDbLine") (10 18585.9728506787
2183.257918552 0.0) (11 18585.9728506787 1283.9366515837 0.0))
((0 . "LINE") (100 . "AcDbEntity") (8 . "WINDOWS") (62 . 7) (370 . 13) (100 . "AcDbLine") (10 17805.4298642534
2138.0090497738 0.0) (11 17805.4298642534 1282.6313914027 0.0))
((0 . "LINE") (100 . "AcDbEntity") (8 . "WINDOWS") (62 . 7) (370 . 13) (100 . "AcDbLine") (10 18529.4117647059
2138.0090497738 0.0) (11 18529.4117647059 1322.82239819 0.0))
((0 . "LINE") (100 . "AcDbEntity") (8 . "WINDOWS") (62 . 7) (370 . 13) (100 . "AcDbLine") (10 18133.4841628959
2283.9572724025 0.0) (11 18133.4841628959 1270.739061086 0.0))
((0 . "LINE") (100 . "AcDbEntity") (8 . "WINDOWS") (62 . 7) (370 . 13) (100 . "AcDbLine") (10 18201.3574660633
2283.9572724025 0.0) (11 18201.3574660633 1248.1146266968 0.0))
((0 . "LINE") (100 . "AcDbEntity") (8 . "WINDOWS") (62 . 7) (370 . 13) (100 . "AcDbLine") (10 18076.9230769231
2613.1221719457 0.0) (11 18257.9185520362 2613.1221719457 0.0))
((0 . "LINE") (100 . "AcDbEntity") (8 . "WINDOWS") (62 . 7) (370 . 13) (100 . "AcDbLine") (10 18257.9185520362
2613.1221719457 0.0) (11 18235.2467658394 2484.6487168304 0.0))
((0 . "LINE") (100 . "AcDbEntity") (8 . "WINDOWS") (62 . 7) (370 . 13) (100 . "AcDbLine") (10 18235.2467658394
2484.6487168304 0.0) (11 18223.9819004525 2420.814479638 0.0))
((0 . "LINE") (100 . "AcDbEntity") (8 . "WINDOWS") (62 . 7) (370 . 13) (100 . "AcDbLine") (10 18223.9819004525
2420.814479638 0.0) (11 18110.8597285068 2420.814479638 0.0))
((0 . "LINE") (100 . "AcDbEntity") (8 . "WINDOWS") (62 . 7) (370 . 13) (100 . "AcDbLine") (10 18110.8597285068
2420.814479638 0.0) (11 18099.5948631199 2484.6487168304 0.0))
((0 . "LINE") (100 . "AcDbEntity") (8 . "WINDOWS") (62 . 7) (370 . 13) (100 . "AcDbLine") (10 18099.5948631199
2484.6487168304 0.0) (11 18076.9230769231 2613.1221719457 0.0))
((0 . "LINE") (100 . "AcDbEntity") (8 . "WINDOWS") (62 . 7) (370 . 13) (100 . "AcDbLine") (10 8212.6696832579
5113.1221719457 0.0) (11 8212.6696832579 4909.5022624434 0.0))
((0 . "LINE") (100 . "AcDbEntity") (8 . "WINDOWS") (62 . 7) (370 . 13) (100 . "AcDbLine") (10 8212.6696832579
4909.5022624434 0.0) (11 8212.6696832579 3280.5429864253 0.0))
((0 . "LINE") (100 . "AcDbEntity") (8 . "WINDOWS") (62 . 7) (370 . 13) (100 . "AcDbLine") (10 9298.6425339367
5113.1221719457 0.0) (11 9298.6425339367 4909.5022624434 0.0))
((0 . "LINE") (100 . "AcDbEntity") (8 . "WINDOWS") (62 . 7) (370 . 13) (100 . "AcDbLine") (10 9298.6425339367
4909.5022624434 0.0) (11 9298.6425339367 3280.5429864253 0.0))
((0 . "LINE") (100 . "AcDbEntity") (8 . "WINDOWS") (62 . 7) (370 . 13) (100 . "AcDbLine") (10 8212.6696832579
3280.5429864253 0.0) (11 8303.1674208145 3280.5429864253 0.0))
((0 . "LINE") (100 . "AcDbEntity") (8 . "WINDOWS") (62 . 7) (370 . 13) (100 . "AcDbLine") (10 8303.1674208145
3280.5429864253 0.0) (11 8348.4162895928 3280.5429864253 0.0))
((0 . "LINE") (100 . "AcDbEntity") (8 . "WINDOWS") (62 . 7) (370 . 13) (100 . "AcDbLine") (10 8348.4162895928
3280.5429864253 0.0) (11 9162.8959276018 3280.5429864253 0.0))
((0 . "LINE") (100 . "AcDbEntity") (8 . "WINDOWS") (62 . 7) (370 . 13) (100 . "AcDbLine") (10 9162.8959276018
3280.5429864253 0.0) (11 9208.1447963801 3280.5429864253 0.0))
((0 . "LINE") (100 . "AcDbEntity") (8 . "WINDOWS") (62 . 7) (370 . 13) (100 . "AcDbLine") (10 9208.1447963801
3280.5429864253 0.0) (11 9298.6425339367 3280.5429864253 0.0))
((0 . "LINE") (100 . "AcDbEntity") (8 . "WINDOWS") (62 . 7) (370 . 13) (100 . "AcDbLine") (10 8303.1674208145
5067.8733031674 0.0) (11 8303.1674208145 3280.5429864253 0.0))
((0 . "LINE") (100 . "AcDbEntity") (8 . "WINDOWS") (62 . 7) (370 . 13) (100 . "AcDbLine") (10 9208.1447963801
5067.8733031674 0.0) (11 9208.1447963801 3280.5429864253 0.0))
((0 . "LINE") (100 . "AcDbEntity") (8 . "WINDOWS") (62 . 7) (370 . 13) (100 . "AcDbLine") (10 8348.4162895928
5022.6244343891 0.0) (11 8348.4162895928 4389.1402714932 0.0))
((0 . "LINE") (100 . "AcDbEntity") (8 . "WINDOWS") (62 . 7) (370 . 13) (100 . "AcDbLine") (10 8348.4162895928
4389.1402714932 0.0) (11 8348.4162895928 3280.5429864253 0.0))
((0 . "LINE") (100 . "AcDbEntity") (8 . "WINDOWS") (62 . 7) (370 . 13) (100 . "AcDbLine") (10 9162.8959276018
5022.6244343891 0.0) (11 9162.8959276018 4389.1402714932 0.0))
((0 . "LINE") (100 . "AcDbEntity") (8 . "WINDOWS") (62 . 7) (370 . 13) (100 . "AcDbLine") (10 9162.8959276018
4389.1402714932 0.0) (11 9162.8959276018 3280.5429864253 0.0))
((0 . "LINE") (100 . "AcDbEntity") (8 . "WINDOWS") (62 . 7) (370 . 13) (100 . "AcDbLine") (10 8721.7194570136
5213.8390258257 0.0) (11 8721.7194570136 4389.1402714932 0.0))
((0 . "LINE") (100 . "AcDbEntity") (8 . "WINDOWS") (62 . 7) (370 . 13) (100 . "AcDbLine") (10 8789.592760181
5213.8390258257 0.0) (11 8789.592760181 4389.1402714932 0.0))
((0 . "LINE") (100 . "AcDbEntity") (8 . "WINDOWS") (62 . 7) (370 . 13) (100 . "AcDbLine") (10 8348.4162895928
4389.1402714932 0.0) (11 8721.7194570136 4389.1402714932 0.0))
((0 . "LINE") (100 . "AcDbEntity") (8 . "WINDOWS") (62 . 7) (370 . 13) (100 . "AcDbLine") (10 8721.7194570136
4389.1402714932 0.0) (11 8789.592760181 4389.1402714932 0.0))
((0 . "LINE") (100 . "AcDbEntity") (8 . "WINDOWS") (62 . 7) (370 . 13) (100 . "AcDbLine") (10 8789.592760181
4389.1402714932 0.0) (11 9162.8959276018 4389.1402714932 0.0))
((0 . "LINE") (100 . "AcDbEntity") (8 . "WINDOWS") (62 . 7) (370 . 13) (100 . "AcDbLine") (10 8404.9773755656
4276.0180995475 0.0) (11 9106.334841629 4276.0180995475 0.0))
((0 . "LINE") (100 . "AcDbEntity") (8 . "WINDOWS") (62 . 7) (370 . 13) (100 . "AcDbLine") (10 9106.334841629
4276.0180995475 0.0) (11 9106.334841629 3337.1040723982 0.0))
((0 . "LINE") (100 . "AcDbEntity") (8 . "WINDOWS") (62 . 7) (370 . 13) (100 . "AcDbLine") (10 9106.334841629
3337.1040723982 0.0) (11 8404.9773755656 3337.1040723982 0.0))
((0 . "LINE") (100 . "AcDbEntity") (8 . "WINDOWS") (62 . 7) (370 . 13) (100 . "AcDbLine") (10 8404.9773755656
3337.1040723982 0.0) (11 8404.9773755656 4276.0180995475 0.0))
((0 . "LINE") (100 . "AcDbEntity") (8 . "WINDOWS") (62 . 7) (370 . 13) (100 . "AcDbLine") (10 8371.0407239819
4321.2669683258 0.0) (11 9140.2714932127 4321.2669683258 0.0))
((0 . "LINE") (100 . "AcDbEntity") (8 . "WINDOWS") (62 . 7) (370 . 13) (100 . "AcDbLine") (10 9140.2714932127
4321.2669683258 0.0) (11 9140.2714932127 3291.8552036199 0.0))
((0 . "LINE") (100 . "AcDbEntity") (8 . "WINDOWS") (62 . 7) (370 . 13) (100 . "AcDbLine") (10 9140.2714932127
3291.8552036199 0.0) (11 8371.0407239819 3291.8552036199 0.0))
((0 . "LINE") (100 . "AcDbEntity") (8 . "WINDOWS") (62 . 7) (370 . 13) (100 . "AcDbLine") (10 8371.0407239819
3291.8552036199 0.0) (11 8371.0407239819 4321.2669683258 0.0))
((0 . "LINE") (100 . "AcDbEntity") (8 . "WINDOWS") (62 . 7) (370 . 13) (100 . "AcDbLine") (10 7963.8009049774
2058.8235294118 0.0) (11 7963.8009049774 192.3076923077 0.0))
((0 . "LINE") (100 . "AcDbEntity") (8 . "WINDOWS") (62 . 7) (370 . 13) (100 . "AcDbLine") (10 7963.8009049774
192.3076923077 0.0) (11 8042.9864253394 192.3076923077 0.0))
((0 . "LINE") (100 . "AcDbEntity") (8 . "WINDOWS") (62 . 7) (370 . 13) (100 . "AcDbLine") (10 8042.9864253394
192.3076923077 0.0) (11 8099.5475113122 192.3076923077 0.0))
((0 . "LINE") (100 . "AcDbEntity") (8 . "WINDOWS") (62 . 7) (370 . 13) (100 . "AcDbLine") (10 8099.5475113122
192.3076923077 0.0) (11 8710.407239819 192.3076923077 0.0))
((0 . "LINE") (100 . "AcDbEntity") (8 . "WINDOWS") (62 . 7) (370 . 13) (100 . "AcDbLine") (10 8710.407239819
192.3076923077 0.0) (11 8800.9049773756 192.3076923077 0.0))
((0 . "LINE") (100 . "AcDbEntity") (8 . "WINDOWS") (62 . 7) (370 . 13) (100 . "AcDbLine") (10 8800.9049773756
192.3076923077 0.0) (11 9411.7647058824 192.3076923077 0.0))
((0 . "LINE") (100 . "AcDbEntity") (8 . "WINDOWS") (62 . 7) (370 . 13) (100 . "AcDbLine") (10 9411.7647058824
192.3076923077 0.0) (11 9468.3257918552 192.3076923077 0.0))
((0 . "LINE") (100 . "AcDbEntity") (8 . "WINDOWS") (62 . 7) (370 . 13) (100 . "AcDbLine") (10 9468.3257918552
192.3076923077 0.0) (11 9547.5113122172 192.3076923077 0.0))
((0 . "LINE") (100 . "AcDbEntity") (8 . "WINDOWS") (62 . 7) (370 . 13) (100 . "AcDbLine") (10 8042.9864253394
2024.8868778281 0.0) (11 8042.9864253394 192.3076923077 0.0))
((0 . "LINE") (100 . "AcDbEntity") (8 . "WINDOWS") (62 . 7) (370 . 13) (100 . "AcDbLine") (10 9468.3257918552
2024.8868778281 0.0) (11 9468.3257918552 192.3076923077 0.0))
((0 . "LINE") (100 . "AcDbEntity") (8 . "WINDOWS") (62 . 7) (370 . 13) (100 . "AcDbLine") (10 8099.5475113122
1979.6380090498 0.0) (11 8099.5475113122 984.1628959276 0.0))
((0 . "LINE") (100 . "AcDbEntity") (8 . "WINDOWS") (62 . 7) (370 . 13) (100 . "AcDbLine") (10 8099.5475113122
984.1628959276 0.0) (11 8099.5475113122 904.9773755656 0.0))
((0 . "LINE") (100 . "AcDbEntity") (8 . "WINDOWS") (62 . 7) (370 . 13) (100 . "AcDbLine") (10 8099.5475113122
904.9773755656 0.0) (11 8099.5475113122 192.3076923077 0.0))
((0 . "LINE") (100 . "AcDbEntity") (8 . "WINDOWS") (62 . 7) (370 . 13) (100 . "AcDbLine") (10 9411.7647058824
1979.6380090498 0.0) (11 9411.7647058824 984.1628959276 0.0))
((0 . "LINE") (100 . "AcDbEntity") (8 . "WINDOWS") (62 . 7) (370 . 13) (100 . "AcDbLine") (10 9411.7647058824
984.1628959276 0.0) (11 9411.7647058824 904.9773755656 0.0))
((0 . "LINE") (100 . "AcDbEntity") (8 . "WINDOWS") (62 . 7) (370 . 13) (100 . "AcDbLine") (10 9411.7647058824
904.9773755656 0.0) (11 9411.7647058824 192.3076923077 0.0))
((0 . "LINE") (100 . "AcDbEntity") (8 . "WINDOWS") (62 . 7) (370 . 13) (100 . "AcDbLine") (10 8710.407239819
2227.4714479638 0.0) (11 8710.407239819 984.1628959276 0.0))
((0 . "LINE") (100 . "AcDbEntity") (8 . "WINDOWS") (62 . 7) (370 . 13) (100 . "AcDbLine") (10 8710.407239819
984.1628959276 0.0) (11 8710.407239819 904.9773755656 0.0))
((0 . "LINE") (100 . "AcDbEntity") (8 . "WINDOWS") (62 . 7) (370 . 13) (100 . "AcDbLine") (10 8710.407239819
904.9773755656 0.0) (11 8710.407239819 192.3076923077 0.0))
((0 . "LINE") (100 . "AcDbEntity") (8 . "WINDOWS") (62 . 7) (370 . 13) (100 . "AcDbLine") (10 8800.9049773756
2227.4714479638 0.0) (11 8800.9049773756 984.1628959276 0.0))
((0 . "LINE") (100 . "AcDbEntity") (8 . "WINDOWS") (62 . 7) (370 . 13) (100 . "AcDbLine") (10 8800.9049773756
984.1628959276 0.0) (11 8800.9049773756 904.9773755656 0.0))
((0 . "LINE") (100 . "AcDbEntity") (8 . "WINDOWS") (62 . 7) (370 . 13) (100 . "AcDbLine") (10 8800.9049773756
904.9773755656 0.0) (11 8800.9049773756 192.3076923077 0.0))
((0 . "LINE") (100 . "AcDbEntity") (8 . "WINDOWS") (62 . 7) (370 . 13) (100 . "AcDbLine") (10 8099.5475113122
984.1628959276 0.0) (11 8710.407239819 984.1628959276 0.0))
((0 . "LINE") (100 . "AcDbEntity") (8 . "WINDOWS") (62 . 7) (370 . 13) (100 . "AcDbLine") (10 8710.407239819
984.1628959276 0.0) (11 8800.9049773756 984.1628959276 0.0))
((0 . "LINE") (100 . "AcDbEntity") (8 . "WINDOWS") (62 . 7) (370 . 13) (100 . "AcDbLine") (10 8800.9049773756
984.1628959276 0.0) (11 9411.7647058824 984.1628959276 0.0))
((0 . "LINE") (100 . "AcDbEntity") (8 . "WINDOWS") (62 . 7) (370 . 13) (100 . "AcDbLine") (10 8099.5475113122
904.9773755656 0.0) (11 8710.407239819 904.9773755656 0.0))
((0 . "LINE") (100 . "AcDbEntity") (8 . "WINDOWS") (62 . 7) (370 . 13) (100 . "AcDbLine") (10 8710.407239819
904.9773755656 0.0) (11 8800.9049773756 904.9773755656 0.0))
((0 . "LINE") (100 . "AcDbEntity") (8 . "WINDOWS") (62 . 7) (370 . 13) (100 . "AcDbLine") (10 8800.9049773756
904.9773755656 0.0) (11 9411.7647058824 904.9773755656 0.0))
((0 . "LINE") (100 . "AcDbEntity") (8 . "WINDOWS") (62 . 7) (370 . 13) (100 . "AcDbLine") (10 8201.3574660633
791.8552036199 0.0) (11 8540.7239819005 791.8552036199 0.0))
((0 . "LINE") (100 . "AcDbEntity") (8 . "WINDOWS") (62 . 7) (370 . 13) (100 . "AcDbLine") (10 8540.7239819005
791.8552036199 0.0) (11 8540.7239819005 305.4298642534 0.0))
((0 . "LINE") (100 . "AcDbEntity") (8 . "WINDOWS") (62 . 7) (370 . 13) (100 . "AcDbLine") (10 8540.7239819005
305.4298642534 0.0) (11 8201.3574660633 305.4298642534 0.0))
((0 . "LINE") (100 . "AcDbEntity") (8 . "WINDOWS") (62 . 7) (370 . 13) (100 . "AcDbLine") (10 8201.3574660633
305.4298642534 0.0) (11 8201.3574660633 791.8552036199 0.0))
((0 . "LINE") (100 . "AcDbEntity") (8 . "WINDOWS") (62 . 7) (370 . 13) (100 . "AcDbLine") (10 8246.6063348416
746.6063348416 0.0) (11 8495.4751131222 746.6063348416 0.0))
((0 . "LINE") (100 . "AcDbEntity") (8 . "WINDOWS") (62 . 7) (370 . 13) (100 . "AcDbLine") (10 8495.4751131222
746.6063348416 0.0) (11 8495.4751131222 361.9909502262 0.0))
((0 . "LINE") (100 . "AcDbEntity") (8 . "WINDOWS") (62 . 7) (370 . 13) (100 . "AcDbLine") (10 8495.4751131222
361.9909502262 0.0) (11 8246.6063348416 361.9909502262 0.0))
((0 . "LINE") (100 . "AcDbEntity") (8 . "WINDOWS") (62 . 7) (370 . 13) (100 . "AcDbLine") (10 8246.6063348416
361.9909502262 0.0) (11 8246.6063348416 746.6063348416 0.0))
((0 . "LINE") (100 . "AcDbEntity") (8 . "WINDOWS") (62 . 7) (370 . 13) (100 . "AcDbLine") (10 8902.7149321267
791.8552036199 0.0) (11 9242.0814479638 791.8552036199 0.0))
((0 . "LINE") (100 . "AcDbEntity") (8 . "WINDOWS") (62 . 7) (370 . 13) (100 . "AcDbLine") (10 9242.0814479638
791.8552036199 0.0) (11 9242.0814479638 305.4298642534 0.0))
((0 . "LINE") (100 . "AcDbEntity") (8 . "WINDOWS") (62 . 7) (370 . 13) (100 . "AcDbLine") (10 9242.0814479638
305.4298642534 0.0) (11 8902.7149321267 305.4298642534 0.0))
((0 . "LINE") (100 . "AcDbEntity") (8 . "WINDOWS") (62 . 7) (370 . 13) (100 . "AcDbLine") (10 8902.7149321267
305.4298642534 0.0) (11 8902.7149321267 791.8552036199 0.0))
((0 . "LINE") (100 . "AcDbEntity") (8 . "WINDOWS") (62 . 7) (370 . 13) (100 . "AcDbLine") (10 8947.963800905
746.6063348416 0.0) (11 9196.8325791855 746.6063348416 0.0))
((0 . "LINE") (100 . "AcDbEntity") (8 . "WINDOWS") (62 . 7) (370 . 13) (100 . "AcDbLine") (10 9196.8325791855
746.6063348416 0.0) (11 9196.8325791855 361.9909502262 0.0))
((0 . "LINE") (100 . "AcDbEntity") (8 . "WINDOWS") (62 . 7) (370 . 13) (100 . "AcDbLine") (10 9196.8325791855
361.9909502262 0.0) (11 8947.963800905 361.9909502262 0.0))
((0 . "LINE") (100 . "AcDbEntity") (8 . "WINDOWS") (62 . 7) (370 . 13) (100 . "AcDbLine") (10 8947.963800905
361.9909502262 0.0) (11 8947.963800905 746.6063348416 0.0))
((0 . "LINE") (100 . "AcDbEntity") (8 . "WINDOWS") (62 . 7) (370 . 13) (100 . "AcDbLine") (10 8665.1583710407
2556.5610859729 0.0) (11 8846.1538461538 2556.5610859729 0.0))
((0 . "LINE") (100 . "AcDbEntity") (8 . "WINDOWS") (62 . 7) (370 . 13) (100 . "AcDbLine") (10 8846.1538461538
2556.5610859729 0.0) (11 8817.8932139859 2396.4175036879 0.0))
((0 . "LINE") (100 . "AcDbEntity") (8 . "WINDOWS") (62 . 7) (370 . 13) (100 . "AcDbLine") (10 8817.8932139859
2396.4175036879 0.0) (11 8812.2171945701 2364.2533936652 0.0))
((0 . "LINE") (100 . "AcDbEntity") (8 . "WINDOWS") (62 . 7) (370 . 13) (100 . "AcDbLine") (10 8812.2171945701
2364.2533936652 0.0) (11 8699.0950226244 2364.2533936652 0.0))
((0 . "LINE") (100 . "AcDbEntity") (8 . "WINDOWS") (62 . 7) (370 . 13) (100 . "AcDbLine") (10 8699.0950226244
2364.2533936652 0.0) (11 8693.4190032087 2396.4175036879 0.0))
((0 . "LINE") (100 . "AcDbEntity") (8 . "WINDOWS") (62 . 7) (370 . 13) (100 . "AcDbLine") (10 8693.4190032087
2396.4175036879 0.0) (11 8665.1583710407 2556.5610859729 0.0))
((0 . "LINE") (100 . "AcDbEntity") (8 . "WINDOWS") (62 . 7) (370 . 13) (100 . "AcDbLine") (10 10712.6696832579
5113.1221719457 0.0) (11 10712.6696832579 4909.5022624434 0.0))
((0 . "LINE") (100 . "AcDbEntity") (8 . "WINDOWS") (62 . 7) (370 . 13) (100 . "AcDbLine") (10 10712.6696832579
4909.5022624434 0.0) (11 10712.6696832579 3280.5429864253 0.0))
((0 . "LINE") (100 . "AcDbEntity") (8 . "WINDOWS") (62 . 7) (370 . 13) (100 . "AcDbLine") (10 11798.6425339367
5113.1221719457 0.0) (11 11798.6425339367 4909.5022624434 0.0))
((0 . "LINE") (100 . "AcDbEntity") (8 . "WINDOWS") (62 . 7) (370 . 13) (100 . "AcDbLine") (10 11798.6425339367
4909.5022624434 0.0) (11 11798.6425339367 3280.5429864253 0.0))
((0 . "LINE") (100 . "AcDbEntity") (8 . "WINDOWS") (62 . 7) (370 . 13) (100 . "AcDbLine") (10 10712.6696832579
3280.5429864253 0.0) (11 10803.1674208145 3280.5429864253 0.0))
((0 . "LINE") (100 . "AcDbEntity") (8 . "WINDOWS") (62 . 7) (370 . 13) (100 . "AcDbLine") (10 10803.1674208145
3280.5429864253 0.0) (11 10848.4162895928 3280.5429864253 0.0))
((0 . "LINE") (100 . "AcDbEntity") (8 . "WINDOWS") (62 . 7) (370 . 13) (100 . "AcDbLine") (10 10848.4162895928
3280.5429864253 0.0) (11 11662.8959276018 3280.5429864253 0.0))
((0 . "LINE") (100 . "AcDbEntity") (8 . "WINDOWS") (62 . 7) (370 . 13) (100 . "AcDbLine") (10 11662.8959276018
3280.5429864253 0.0) (11 11708.1447963801 3280.5429864253 0.0))
((0 . "LINE") (100 . "AcDbEntity") (8 . "WINDOWS") (62 . 7) (370 . 13) (100 . "AcDbLine") (10 11708.1447963801
3280.5429864253 0.0) (11 11798.6425339367 3280.5429864253 0.0))
((0 . "LINE") (100 . "AcDbEntity") (8 . "WINDOWS") (62 . 7) (370 . 13) (100 . "AcDbLine") (10 10803.1674208145
5067.8733031674 0.0) (11 10803.1674208145 3280.5429864253 0.0))
((0 . "LINE") (100 . "AcDbEntity") (8 . "WINDOWS") (62 . 7) (370 . 13) (100 . "AcDbLine") (10 11708.1447963801
5067.8733031674 0.0) (11 11708.1447963801 3280.5429864253 0.0))
((0 . "LINE") (100 . "AcDbEntity") (8 . "WINDOWS") (62 . 7) (370 . 13) (100 . "AcDbLine") (10 10848.4162895928
5022.6244343891 0.0) (11 10848.4162895928 4389.1402714932 0.0))
((0 . "LINE") (100 . "AcDbEntity") (8 . "WINDOWS") (62 . 7) (370 . 13) (100 . "AcDbLine") (10 10848.4162895928
4389.1402714932 0.0) (11 10848.4162895928 3280.5429864253 0.0))
((0 . "LINE") (100 . "AcDbEntity") (8 . "WINDOWS") (62 . 7) (370 . 13) (100 . "AcDbLine") (10 11662.8959276018
5022.6244343891 0.0) (11 11662.8959276018 4389.1402714932 0.0))
((0 . "LINE") (100 . "AcDbEntity") (8 . "WINDOWS") (62 . 7) (370 . 13) (100 . "AcDbLine") (10 11662.8959276018
4389.1402714932 0.0) (11 11662.8959276018 3280.5429864253 0.0))
((0 . "LINE") (100 . "AcDbEntity") (8 . "WINDOWS") (62 . 7) (370 . 13) (100 . "AcDbLine") (10 11221.7194570136
5213.8390258257 0.0) (11 11221.7194570136 4389.1402714932 0.0))
((0 . "LINE") (100 . "AcDbEntity") (8 . "WINDOWS") (62 . 7) (370 . 13) (100 . "AcDbLine") (10 11289.592760181
5213.8390258257 0.0) (11 11289.592760181 4389.1402714932 0.0))
((0 . "LINE") (100 . "AcDbEntity") (8 . "WINDOWS") (62 . 7) (370 . 13) (100 . "AcDbLine") (10 10848.4162895928
4389.1402714932 0.0) (11 11221.7194570136 4389.1402714932 0.0))
((0 . "LINE") (100 . "AcDbEntity") (8 . "WINDOWS") (62 . 7) (370 . 13) (100 . "AcDbLine") (10 11221.7194570136
4389.1402714932 0.0) (11 11289.592760181 4389.1402714932 0.0))
((0 . "LINE") (100 . "AcDbEntity") (8 . "WINDOWS") (62 . 7) (370 . 13) (100 . "AcDbLine") (10 11289.592760181
4389.1402714932 0.0) (11 11662.8959276018 4389.1402714932 0.0))
((0 . "LINE") (100 . "AcDbEntity") (8 . "WINDOWS") (62 . 7) (370 . 13) (100 . "AcDbLine") (10 10904.9773755656
4276.0180995475 0.0) (11 11606.334841629 4276.0180995475 0.0))
((0 . "LINE") (100 . "AcDbEntity") (8 . "WINDOWS") (62 . 7) (370 . 13) (100 . "AcDbLine") (10 11606.334841629
4276.0180995475 0.0) (11 11606.334841629 3337.1040723982 0.0))
((0 . "LINE") (100 . "AcDbEntity") (8 . "WINDOWS") (62 . 7) (370 . 13) (100 . "AcDbLine") (10 11606.334841629
3337.1040723982 0.0) (11 10904.9773755656 3337.1040723982 0.0))
((0 . "LINE") (100 . "AcDbEntity") (8 . "WINDOWS") (62 . 7) (370 . 13) (100 . "AcDbLine") (10 10904.9773755656
3337.1040723982 0.0) (11 10904.9773755656 4276.0180995475 0.0))
((0 . "LINE") (100 . "AcDbEntity") (8 . "WINDOWS") (62 . 7) (370 . 13) (100 . "AcDbLine") (10 10871.0407239819
4321.2669683258 0.0) (11 11640.2714932127 4321.2669683258 0.0))
((0 . "LINE") (100 . "AcDbEntity") (8 . "WINDOWS") (62 . 7) (370 . 13) (100 . "AcDbLine") (10 11640.2714932127
4321.2669683258 0.0) (11 11640.2714932127 3291.8552036199 0.0))
((0 . "LINE") (100 . "AcDbEntity") (8 . "WINDOWS") (62 . 7) (370 . 13) (100 . "AcDbLine") (10 11640.2714932127
3291.8552036199 0.0) (11 10871.0407239819 3291.8552036199 0.0))
((0 . "LINE") (100 . "AcDbEntity") (8 . "WINDOWS") (62 . 7) (370 . 13) (100 . "AcDbLine") (10 10871.0407239819
3291.8552036199 0.0) (11 10871.0407239819 4321.2669683258 0.0))
((0 . "LINE") (100 . "AcDbEntity") (8 . "WINDOWS") (62 . 7) (370 . 13) (100 . "AcDbLine") (10 10463.8009049774
2058.8235294118 0.0) (11 10463.8009049774 192.3076923077 0.0))
((0 . "LINE") (100 . "AcDbEntity") (8 . "WINDOWS") (62 . 7) (370 . 13) (100 . "AcDbLine") (10 12047.5113122172
2058.8235294118 0.0) (11 12047.5113122172 192.3076923077 0.0))
((0 . "LINE") (100 . "AcDbEntity") (8 . "WINDOWS") (62 . 7) (370 . 13) (100 . "AcDbLine") (10 10463.8009049774
192.3076923077 0.0) (11 10542.9864253394 192.3076923077 0.0))
((0 . "LINE") (100 . "AcDbEntity") (8 . "WINDOWS") (62 . 7) (370 . 13) (100 . "AcDbLine") (10 10542.9864253394
192.3076923077 0.0) (11 10599.5475113122 192.3076923077 0.0))
((0 . "LINE") (100 . "AcDbEntity") (8 . "WINDOWS") (62 . 7) (370 . 13) (100 . "AcDbLine") (10 10599.5475113122
192.3076923077 0.0) (11 11210.407239819 192.3076923077 0.0))
((0 . "LINE") (100 . "AcDbEntity") (8 . "WINDOWS") (62 . 7) (370 . 13) (100 . "AcDbLine") (10 11210.407239819
192.3076923077 0.0) (11 11300.9049773756 192.3076923077 0.0))
((0 . "LINE") (100 . "AcDbEntity") (8 . "WINDOWS") (62 . 7) (370 . 13) (100 . "AcDbLine") (10 11300.9049773756
192.3076923077 0.0) (11 11911.7647058824 192.3076923077 0.0))
((0 . "LINE") (100 . "AcDbEntity") (8 . "WINDOWS") (62 . 7) (370 . 13) (100 . "AcDbLine") (10 11911.7647058824
192.3076923077 0.0) (11 11968.3257918552 192.3076923077 0.0))
((0 . "LINE") (100 . "AcDbEntity") (8 . "WINDOWS") (62 . 7) (370 . 13) (100 . "AcDbLine") (10 11968.3257918552
192.3076923077 0.0) (11 12036.1990950226 192.3076923077 0.0))
((0 . "LINE") (100 . "AcDbEntity") (8 . "WINDOWS") (62 . 7) (370 . 13) (100 . "AcDbLine") (10 12036.1990950226
192.3076923077 0.0) (11 12047.5113122172 192.3076923077 0.0))
((0 . "LINE") (100 . "AcDbEntity") (8 . "WINDOWS") (62 . 7) (370 . 13) (100 . "AcDbLine") (10 10542.9864253394
2024.8868778281 0.0) (11 10542.9864253394 192.3076923077 0.0))
((0 . "LINE") (100 . "AcDbEntity") (8 . "WINDOWS") (62 . 7) (370 . 13) (100 . "AcDbLine") (10 11968.3257918552
2024.8868778281 0.0) (11 11968.3257918552 192.3076923077 0.0))
((0 . "LINE") (100 . "AcDbEntity") (8 . "WINDOWS") (62 . 7) (370 . 13) (100 . "AcDbLine") (10 10599.5475113122
1979.6380090498 0.0) (11 10599.5475113122 984.1628959276 0.0))
((0 . "LINE") (100 . "AcDbEntity") (8 . "WINDOWS") (62 . 7) (370 . 13) (100 . "AcDbLine") (10 10599.5475113122
984.1628959276 0.0) (11 10599.5475113122 904.9773755656 0.0))
((0 . "LINE") (100 . "AcDbEntity") (8 . "WINDOWS") (62 . 7) (370 . 13) (100 . "AcDbLine") (10 10599.5475113122
904.9773755656 0.0) (11 10599.5475113122 192.3076923077 0.0))
((0 . "LINE") (100 . "AcDbEntity") (8 . "WINDOWS") (62 . 7) (370 . 13) (100 . "AcDbLine") (10 11911.7647058824
1979.6380090498 0.0) (11 11911.7647058824 984.1628959276 0.0))
((0 . "LINE") (100 . "AcDbEntity") (8 . "WINDOWS") (62 . 7) (370 . 13) (100 . "AcDbLine") (10 11911.7647058824
984.1628959276 0.0) (11 11911.7647058824 904.9773755656 0.0))
((0 . "LINE") (100 . "AcDbEntity") (8 . "WINDOWS") (62 . 7) (370 . 13) (100 . "AcDbLine") (10 11911.7647058824
904.9773755656 0.0) (11 11911.7647058824 192.3076923077 0.0))
((0 . "LINE") (100 . "AcDbEntity") (8 . "WINDOWS") (62 . 7) (370 . 13) (100 . "AcDbLine") (10 11210.407239819
2227.4714479638 0.0) (11 11210.407239819 984.1628959276 0.0))
((0 . "LINE") (100 . "AcDbEntity") (8 . "WINDOWS") (62 . 7) (370 . 13) (100 . "AcDbLine") (10 11210.407239819
984.1628959276 0.0) (11 11210.407239819 904.9773755656 0.0))
((0 . "LINE") (100 . "AcDbEntity") (8 . "WINDOWS") (62 . 7) (370 . 13) (100 . "AcDbLine") (10 11210.407239819
904.9773755656 0.0) (11 11210.407239819 192.3076923077 0.0))
((0 . "LINE") (100 . "AcDbEntity") (8 . "WINDOWS") (62 . 7) (370 . 13) (100 . "AcDbLine") (10 11300.9049773756
2227.4714479638 0.0) (11 11300.9049773756 984.1628959276 0.0))
((0 . "LINE") (100 . "AcDbEntity") (8 . "WINDOWS") (62 . 7) (370 . 13) (100 . "AcDbLine") (10 11300.9049773756
984.1628959276 0.0) (11 11300.9049773756 904.9773755656 0.0))
((0 . "LINE") (100 . "AcDbEntity") (8 . "WINDOWS") (62 . 7) (370 . 13) (100 . "AcDbLine") (10 11300.9049773756
904.9773755656 0.0) (11 11300.9049773756 192.3076923077 0.0))
((0 . "LINE") (100 . "AcDbEntity") (8 . "WINDOWS") (62 . 7) (370 . 13) (100 . "AcDbLine") (10 10599.5475113122
984.1628959276 0.0) (11 11210.407239819 984.1628959276 0.0))
((0 . "LINE") (100 . "AcDbEntity") (8 . "WINDOWS") (62 . 7) (370 . 13) (100 . "AcDbLine") (10 11210.407239819
984.1628959276 0.0) (11 11300.9049773756 984.1628959276 0.0))
((0 . "LINE") (100 . "AcDbEntity") (8 . "WINDOWS") (62 . 7) (370 . 13) (100 . "AcDbLine") (10 11300.9049773756
984.1628959276 0.0) (11 11911.7647058824 984.1628959276 0.0))
((0 . "LINE") (100 . "AcDbEntity") (8 . "WINDOWS") (62 . 7) (370 . 13) (100 . "AcDbLine") (10 10599.5475113122
904.9773755656 0.0) (11 11210.407239819 904.9773755656 0.0))
((0 . "LINE") (100 . "AcDbEntity") (8 . "WINDOWS") (62 . 7) (370 . 13) (100 . "AcDbLine") (10 11210.407239819
904.9773755656 0.0) (11 11300.9049773756 904.9773755656 0.0))
((0 . "LINE") (100 . "AcDbEntity") (8 . "WINDOWS") (62 . 7) (370 . 13) (100 . "AcDbLine") (10 11300.9049773756
904.9773755656 0.0) (11 11911.7647058824 904.9773755656 0.0))
((0 . "LINE") (100 . "AcDbEntity") (8 . "WINDOWS") (62 . 7) (370 . 13) (100 . "AcDbLine") (10 10701.3574660633
791.8552036199 0.0) (11 11040.7239819005 791.8552036199 0.0))
((0 . "LINE") (100 . "AcDbEntity") (8 . "WINDOWS") (62 . 7) (370 . 13) (100 . "AcDbLine") (10 11040.7239819005
791.8552036199 0.0) (11 11040.7239819005 305.4298642534 0.0))
((0 . "LINE") (100 . "AcDbEntity") (8 . "WINDOWS") (62 . 7) (370 . 13) (100 . "AcDbLine") (10 11040.7239819005
305.4298642534 0.0) (11 10701.3574660633 305.4298642534 0.0))
((0 . "LINE") (100 . "AcDbEntity") (8 . "WINDOWS") (62 . 7) (370 . 13) (100 . "AcDbLine") (10 10701.3574660633
305.4298642534 0.0) (11 10701.3574660633 791.8552036199 0.0))
((0 . "LINE") (100 . "AcDbEntity") (8 . "WINDOWS") (62 . 7) (370 . 13) (100 . "AcDbLine") (10 10746.6063348416
746.6063348416 0.0) (11 10995.4751131222 746.6063348416 0.0))
((0 . "LINE") (100 . "AcDbEntity") (8 . "WINDOWS") (62 . 7) (370 . 13) (100 . "AcDbLine") (10 10995.4751131222
746.6063348416 0.0) (11 10995.4751131222 361.9909502262 0.0))
((0 . "LINE") (100 . "AcDbEntity") (8 . "WINDOWS") (62 . 7) (370 . 13) (100 . "AcDbLine") (10 10995.4751131222
361.9909502262 0.0) (11 10746.6063348416 361.9909502262 0.0))
((0 . "LINE") (100 . "AcDbEntity") (8 . "WINDOWS") (62 . 7) (370 . 13) (100 . "AcDbLine") (10 10746.6063348416
361.9909502262 0.0) (11 10746.6063348416 746.6063348416 0.0))
((0 . "LINE") (100 . "AcDbEntity") (8 . "WINDOWS") (62 . 7) (370 . 13) (100 . "AcDbLine") (10 11402.7149321267
791.8552036199 0.0) (11 11742.0814479638 791.8552036199 0.0))
((0 . "LINE") (100 . "AcDbEntity") (8 . "WINDOWS") (62 . 7) (370 . 13) (100 . "AcDbLine") (10 11742.0814479638
791.8552036199 0.0) (11 11742.0814479638 305.4298642534 0.0))
((0 . "LINE") (100 . "AcDbEntity") (8 . "WINDOWS") (62 . 7) (370 . 13) (100 . "AcDbLine") (10 11742.0814479638
305.4298642534 0.0) (11 11402.7149321267 305.4298642534 0.0))
((0 . "LINE") (100 . "AcDbEntity") (8 . "WINDOWS") (62 . 7) (370 . 13) (100 . "AcDbLine") (10 11402.7149321267
305.4298642534 0.0) (11 11402.7149321267 791.8552036199 0.0))
((0 . "LINE") (100 . "AcDbEntity") (8 . "WINDOWS") (62 . 7) (370 . 13) (100 . "AcDbLine") (10 11447.963800905
746.6063348416 0.0) (11 11696.8325791855 746.6063348416 0.0))
((0 . "LINE") (100 . "AcDbEntity") (8 . "WINDOWS") (62 . 7) (370 . 13) (100 . "AcDbLine") (10 11696.8325791855
746.6063348416 0.0) (11 11696.8325791855 361.9909502262 0.0))
((0 . "LINE") (100 . "AcDbEntity") (8 . "WINDOWS") (62 . 7) (370 . 13) (100 . "AcDbLine") (10 11696.8325791855
361.9909502262 0.0) (11 11447.963800905 361.9909502262 0.0))
((0 . "LINE") (100 . "AcDbEntity") (8 . "WINDOWS") (62 . 7) (370 . 13) (100 . "AcDbLine") (10 11447.963800905
361.9909502262 0.0) (11 11447.963800905 746.6063348416 0.0))
((0 . "LINE") (100 . "AcDbEntity") (8 . "WINDOWS") (62 . 7) (370 . 13) (100 . "AcDbLine") (10 11165.1583710407
2556.5610859729 0.0) (11 11346.1538461538 2556.5610859729 0.0))
((0 . "LINE") (100 . "AcDbEntity") (8 . "WINDOWS") (62 . 7) (370 . 13) (100 . "AcDbLine") (10 11346.1538461538
2556.5610859729 0.0) (11 11317.8932139859 2396.4175036879 0.0))
((0 . "LINE") (100 . "AcDbEntity") (8 . "WINDOWS") (62 . 7) (370 . 13) (100 . "AcDbLine") (10 11317.8932139859
2396.4175036879 0.0) (11 11312.2171945701 2364.2533936652 0.0))
((0 . "LINE") (100 . "AcDbEntity") (8 . "WINDOWS") (62 . 7) (370 . 13) (100 . "AcDbLine") (10 11312.2171945701
2364.2533936652 0.0) (11 11199.0950226244 2364.2533936652 0.0))
((0 . "LINE") (100 . "AcDbEntity") (8 . "WINDOWS") (62 . 7) (370 . 13) (100 . "AcDbLine") (10 11199.0950226244
2364.2533936652 0.0) (11 11193.4190032087 2396.4175036879 0.0))
((0 . "LINE") (100 . "AcDbEntity") (8 . "WINDOWS") (62 . 7) (370 . 13) (100 . "AcDbLine") (10 11193.4190032087
2396.4175036879 0.0) (11 11165.1583710407 2556.5610859729 0.0))
((0 . "LINE") (100 . "AcDbEntity") (8 . "SOLAR") (62 . 7) (370 . 13) (100 . "AcDbLine") (10 4162.8959276018
8212.6696832579 0.0) (11 4966.0633484163 8212.6696832579 0.0))
((0 . "LINE") (100 . "AcDbEntity") (8 . "SOLAR") (62 . 7) (370 . 13) (100 . "AcDbLine") (10 4966.0633484163
8212.6696832579 0.0) (11 5214.9321266968 7873.3031674208 0.0))
((0 . "LINE") (100 . "AcDbEntity") (8 . "SOLAR") (62 . 7) (370 . 13) (100 . "AcDbLine") (10 5214.9321266968
7873.3031674208 0.0) (11 4366.5158371041 7873.3031674208 0.0))
((0 . "LINE") (100 . "AcDbEntity") (8 . "SOLAR") (62 . 7) (370 . 13) (100 . "AcDbLine") (10 4366.5158371041
7873.3031674208 0.0) (11 4162.8959276018 8212.6696832579 0.0))
((0 . "LINE") (100 . "AcDbEntity") (8 . "SOLAR") (62 . 7) (370 . 13) (100 . "AcDbLine") (10 4203.4502262443
8178.7330316742 0.0) (11 4452.4886877828 8178.7330316742 0.0))
((0 . "LINE") (100 . "AcDbEntity") (8 . "SOLAR") (62 . 7) (370 . 13) (100 . "AcDbLine") (10 4452.4886877828
8178.7330316742 0.0) (11 4721.7194570136 8178.7330316742 0.0))
((0 . "LINE") (100 . "AcDbEntity") (8 . "SOLAR") (62 . 7) (370 . 13) (100 . "AcDbLine") (10 4721.7194570136
8178.7330316742 0.0) (11 4970.757918552 8178.7330316742 0.0))
((0 . "LINE") (100 . "AcDbEntity") (8 . "SOLAR") (62 . 7) (370 . 13) (100 . "AcDbLine") (10 4970.757918552
8178.7330316742 0.0) (11 4980.4196832579 8165.4977375566 0.0))
((0 . "LINE") (100 . "AcDbEntity") (8 . "SOLAR") (62 . 7) (370 . 13) (100 . "AcDbLine") (10 4980.4196832579
8165.4977375566 0.0) (11 5021.6060520362 8109.0780542986 0.0))
((0 . "LINE") (100 . "AcDbEntity") (8 . "SOLAR") (62 . 7) (370 . 13) (100 . "AcDbLine") (10 5021.6060520362
8109.0780542986 0.0) (11 5054.5551470588 8063.9423076923 0.0))
((0 . "LINE") (100 . "AcDbEntity") (8 . "SOLAR") (62 . 7) (370 . 13) (100 . "AcDbLine") (10 5054.5551470588
8063.9423076923 0.0) (11 5094.5647624434 8009.1346153846 0.0))
((0 . "LINE") (100 . "AcDbEntity") (8 . "SOLAR") (62 . 7) (370 . 13) (100 . "AcDbLine") (10 5094.5647624434
8009.1346153846 0.0) (11 5120.4533371041 7973.6708144796 0.0))
((0 . "LINE") (100 . "AcDbEntity") (8 . "SOLAR") (62 . 7) (370 . 13) (100 . "AcDbLine") (10 5120.4533371041
7973.6708144796 0.0) (11 5143.9884049774 7941.4309954751 0.0))
((0 . "LINE") (100 . "AcDbEntity") (8 . "SOLAR") (62 . 7) (370 . 13) (100 . "AcDbLine") (10 5143.9884049774
7941.4309954751 0.0) (11 5168.9479638009 7907.2398190045 0.0))
((0 . "LINE") (100 . "AcDbEntity") (8 . "SOLAR") (62 . 7) (370 . 13) (100 . "AcDbLine") (10 5168.9479638009
7907.2398190045 0.0) (11 4908.7481108597 7907.2398190045 0.0))
((0 . "LINE") (100 . "AcDbEntity") (8 . "SOLAR") (62 . 7) (370 . 13) (100 . "AcDbLine") (10 4908.7481108597
7907.2398190045 0.0) (11 4627.4509841629 7907.2398190045 0.0))
((0 . "LINE") (100 . "AcDbEntity") (8 . "SOLAR") (62 . 7) (370 . 13) (100 . "AcDbLine") (10 4627.4509841629
7907.2398190045 0.0) (11 4367.2511312217 7907.2398190045 0.0))
((0 . "LINE") (100 . "AcDbEntity") (8 . "SOLAR") (62 . 7) (370 . 13) (100 . "AcDbLine") (10 4367.2511312217
7907.2398190045 0.0) (11 4346.6224547511 7941.4309954751 0.0))
((0 . "LINE") (100 . "AcDbEntity") (8 . "SOLAR") (62 . 7) (370 . 13) (100 . "AcDbLine") (10 4346.6224547511
7941.4309954751 0.0) (11 4327.1710972851 7973.6708144796 0.0))
((0 . "LINE") (100 . "AcDbEntity") (8 . "SOLAR") (62 . 7) (370 . 13) (100 . "AcDbLine") (10 4327.1710972851
7973.6708144796 0.0) (11 4305.7746040724 8009.1346153846 0.0))
((0 . "LINE") (100 . "AcDbEntity") (8 . "SOLAR") (62 . 7) (370 . 13) (100 . "AcDbLine") (10 4305.7746040724
8009.1346153846 0.0) (11 4272.7072963801 8063.9423076923 0.0))
((0 . "LINE") (100 . "AcDbEntity") (8 . "SOLAR") (62 . 7) (370 . 13) (100 . "AcDbLine") (10 4272.7072963801
8063.9423076923 0.0) (11 4245.4753959276 8109.0780542986 0.0))
((0 . "LINE") (100 . "AcDbEntity") (8 . "SOLAR") (62 . 7) (370 . 13) (100 . "AcDbLine") (10 4245.4753959276
8109.0780542986 0.0) (11 4211.435520362 8165.4977375566 0.0))
((0 . "LINE") (100 . "AcDbEntity") (8 . "SOLAR") (62 . 7) (370 . 13) (100 . "AcDbLine") (10 4211.435520362
8165.4977375566 0.0) (11 4203.4502262443 8178.7330316742 0.0))
((0 . "LINE") (100 . "AcDbEntity") (8 . "SOLAR") (62 . 7) (370 . 13) (100 . "AcDbLine") (10 4452.4886877828
8178.7330316742 0.0) (11 4461.0180995475 8165.4977375566 0.0))
((0 . "LINE") (100 . "AcDbEntity") (8 . "SOLAR") (62 . 7) (370 . 13) (100 . "AcDbLine") (10 4461.0180995475
8165.4977375566 0.0) (11 4497.3774547511 8109.0780542986 0.0))
((0 . "LINE") (100 . "AcDbEntity") (8 . "SOLAR") (62 . 7) (370 . 13) (100 . "AcDbLine") (10 4497.3774547511
8109.0780542986 0.0) (11 4526.4649321267 8063.9423076923 0.0))
((0 . "LINE") (100 . "AcDbEntity") (8 . "SOLAR") (62 . 7) (370 . 13) (100 . "AcDbLine") (10 4526.4649321267
8063.9423076923 0.0) (11 4561.7854411765 8009.1346153846 0.0))
((0 . "LINE") (100 . "AcDbEntity") (8 . "SOLAR") (62 . 7) (370 . 13) (100 . "AcDbLine") (10 4561.7854411765
8009.1346153846 0.0) (11 4584.63989819 7973.6708144796 0.0))
((0 . "LINE") (100 . "AcDbEntity") (8 . "SOLAR") (62 . 7) (370 . 13) (100 . "AcDbLine") (10 4584.63989819
7973.6708144796 0.0) (11 4605.4166628959 7941.4309954751 0.0))
((0 . "LINE") (100 . "AcDbEntity") (8 . "SOLAR") (62 . 7) (370 . 13) (100 . "AcDbLine") (10 4605.4166628959
7941.4309954751 0.0) (11 4627.4509841629 7907.2398190045 0.0))
((0 . "LINE") (100 . "AcDbEntity") (8 . "SOLAR") (62 . 7) (370 . 13) (100 . "AcDbLine") (10 4721.7194570136
8178.7330316742 0.0) (11 4730.8371040724 8165.4977375566 0.0))
((0 . "LINE") (100 . "AcDbEntity") (8 . "SOLAR") (62 . 7) (370 . 13) (100 . "AcDbLine") (10 4730.8371040724
8165.4977375566 0.0) (11 4769.7039932127 8109.0780542986 0.0))
((0 . "LINE") (100 . "AcDbEntity") (8 . "SOLAR") (62 . 7) (370 . 13) (100 . "AcDbLine") (10 4769.7039932127
8109.0780542986 0.0) (11 4800.7975113122 8063.9423076923 0.0))
((0 . "LINE") (100 . "AcDbEntity") (8 . "SOLAR") (62 . 7) (370 . 13) (100 . "AcDbLine") (10 4800.7975113122
8063.9423076923 0.0) (11 4838.5539253394 8009.1346153846 0.0))
((0 . "LINE") (100 . "AcDbEntity") (8 . "SOLAR") (62 . 7) (370 . 13) (100 . "AcDbLine") (10 4838.5539253394
8009.1346153846 0.0) (11 4862.9845361991 7973.6708144796 0.0))
((0 . "LINE") (100 . "AcDbEntity") (8 . "SOLAR") (62 . 7) (370 . 13) (100 . "AcDbLine") (10 4862.9845361991
7973.6708144796 0.0) (11 4885.1941968326 7941.4309954751 0.0))
((0 . "LINE") (100 . "AcDbEntity") (8 . "SOLAR") (62 . 7) (370 . 13) (100 . "AcDbLine") (10 4885.1941968326
7941.4309954751 0.0) (11 4908.7481108597 7907.2398190045 0.0))
((0 . "LINE") (100 . "AcDbEntity") (8 . "SOLAR") (62 . 7) (370 . 13) (100 . "AcDbLine") (10 4211.435520362
8165.4977375566 0.0) (11 4461.0180995475 8165.4977375566 0.0))
((0 . "LINE") (100 . "AcDbEntity") (8 . "SOLAR") (62 . 7) (370 . 13) (100 . "AcDbLine") (10 4461.0180995475
8165.4977375566 0.0) (11 4730.8371040724 8165.4977375566 0.0))
((0 . "LINE") (100 . "AcDbEntity") (8 . "SOLAR") (62 . 7) (370 . 13) (100 . "AcDbLine") (10 4730.8371040724
8165.4977375566 0.0) (11 4980.4196832579 8165.4977375566 0.0))
((0 . "LINE") (100 . "AcDbEntity") (8 . "SOLAR") (62 . 7) (370 . 13) (100 . "AcDbLine") (10 4245.4753959276
8109.0780542986 0.0) (11 4497.3774547511 8109.0780542986 0.0))
((0 . "LINE") (100 . "AcDbEntity") (8 . "SOLAR") (62 . 7) (370 . 13) (100 . "AcDbLine") (10 4497.3774547511
8109.0780542986 0.0) (11 4769.7039932127 8109.0780542986 0.0))
((0 . "LINE") (100 . "AcDbEntity") (8 . "SOLAR") (62 . 7) (370 . 13) (100 . "AcDbLine") (10 4769.7039932127
8109.0780542986 0.0) (11 5021.6060520362 8109.0780542986 0.0))
((0 . "LINE") (100 . "AcDbEntity") (8 . "SOLAR") (62 . 7) (370 . 13) (100 . "AcDbLine") (10 4272.7072963801
8063.9423076923 0.0) (11 4526.4649321267 8063.9423076923 0.0))
((0 . "LINE") (100 . "AcDbEntity") (8 . "SOLAR") (62 . 7) (370 . 13) (100 . "AcDbLine") (10 4526.4649321267
8063.9423076923 0.0) (11 4800.7975113122 8063.9423076923 0.0))
((0 . "LINE") (100 . "AcDbEntity") (8 . "SOLAR") (62 . 7) (370 . 13) (100 . "AcDbLine") (10 4800.7975113122
8063.9423076923 0.0) (11 5054.5551470588 8063.9423076923 0.0))
((0 . "LINE") (100 . "AcDbEntity") (8 . "SOLAR") (62 . 7) (370 . 13) (100 . "AcDbLine") (10 4305.7746040724
8009.1346153846 0.0) (11 4561.7854411765 8009.1346153846 0.0))
((0 . "LINE") (100 . "AcDbEntity") (8 . "SOLAR") (62 . 7) (370 . 13) (100 . "AcDbLine") (10 4561.7854411765
8009.1346153846 0.0) (11 4838.5539253394 8009.1346153846 0.0))
((0 . "LINE") (100 . "AcDbEntity") (8 . "SOLAR") (62 . 7) (370 . 13) (100 . "AcDbLine") (10 4838.5539253394
8009.1346153846 0.0) (11 5094.5647624434 8009.1346153846 0.0))
((0 . "LINE") (100 . "AcDbEntity") (8 . "SOLAR") (62 . 7) (370 . 13) (100 . "AcDbLine") (10 4327.1710972851
7973.6708144796 0.0) (11 4584.63989819 7973.6708144796 0.0))
((0 . "LINE") (100 . "AcDbEntity") (8 . "SOLAR") (62 . 7) (370 . 13) (100 . "AcDbLine") (10 4584.63989819
7973.6708144796 0.0) (11 4862.9845361991 7973.6708144796 0.0))
((0 . "LINE") (100 . "AcDbEntity") (8 . "SOLAR") (62 . 7) (370 . 13) (100 . "AcDbLine") (10 4862.9845361991
7973.6708144796 0.0) (11 5120.4533371041 7973.6708144796 0.0))
((0 . "LINE") (100 . "AcDbEntity") (8 . "SOLAR") (62 . 7) (370 . 13) (100 . "AcDbLine") (10 4346.6224547511
7941.4309954751 0.0) (11 4605.4166628959 7941.4309954751 0.0))
((0 . "LINE") (100 . "AcDbEntity") (8 . "SOLAR") (62 . 7) (370 . 13) (100 . "AcDbLine") (10 4605.4166628959
7941.4309954751 0.0) (11 4885.1941968326 7941.4309954751 0.0))
((0 . "LINE") (100 . "AcDbEntity") (8 . "SOLAR") (62 . 7) (370 . 13) (100 . "AcDbLine") (10 4885.1941968326
7941.4309954751 0.0) (11 5143.9884049774 7941.4309954751 0.0))
((0 . "LINE") (100 . "AcDbEntity") (8 . "SOLAR") (62 . 7) (370 . 13) (100 . "AcDbLine") (10 5000 8212.6696832579 0.0)
(11 5780.5429864253 8212.6696832579 0.0))
((0 . "LINE") (100 . "AcDbEntity") (8 . "SOLAR") (62 . 7) (370 . 13) (100 . "AcDbLine") (10 5780.5429864253
8212.6696832579 0.0) (11 6029.4117647059 7873.3031674208 0.0))
((0 . "LINE") (100 . "AcDbEntity") (8 . "SOLAR") (62 . 7) (370 . 13) (100 . "AcDbLine") (10 6029.4117647059
7873.3031674208 0.0) (11 5248.8687782805 7873.3031674208 0.0))
((0 . "LINE") (100 . "AcDbEntity") (8 . "SOLAR") (62 . 7) (370 . 13) (100 . "AcDbLine") (10 5248.8687782805
7873.3031674208 0.0) (11 5000 8212.6696832579 0.0))
((0 . "LINE") (100 . "AcDbEntity") (8 . "SOLAR") (62 . 7) (370 . 13) (100 . "AcDbLine") (10 5044.4004524887
8178.7330316742 0.0) (11 5285.0678733032 8178.7330316742 0.0))
((0 . "LINE") (100 . "AcDbEntity") (8 . "SOLAR") (62 . 7) (370 . 13) (100 . "AcDbLine") (10 5285.0678733032
8178.7330316742 0.0) (11 5545.2488687783 8178.7330316742 0.0))
((0 . "LINE") (100 . "AcDbEntity") (8 . "SOLAR") (62 . 7) (370 . 13) (100 . "AcDbLine") (10 5545.2488687783
8178.7330316742 0.0) (11 5785.9162895928 8178.7330316742 0.0))
((0 . "LINE") (100 . "AcDbEntity") (8 . "SOLAR") (62 . 7) (370 . 13) (100 . "AcDbLine") (10 5785.9162895928
8178.7330316742 0.0) (11 5795.6221719457 8165.4977375566 0.0))
((0 . "LINE") (100 . "AcDbEntity") (8 . "SOLAR") (62 . 7) (370 . 13) (100 . "AcDbLine") (10 5795.6221719457
8165.4977375566 0.0) (11 5836.9966063348 8109.0780542986 0.0))
((0 . "LINE") (100 . "AcDbEntity") (8 . "SOLAR") (62 . 7) (370 . 13) (100 . "AcDbLine") (10 5836.9966063348
8109.0780542986 0.0) (11 5871.278280543 8062.3303167421 0.0))
((0 . "LINE") (100 . "AcDbEntity") (8 . "SOLAR") (62 . 7) (370 . 13) (100 . "AcDbLine") (10 5871.278280543
8062.3303167421 0.0) (11 5910.2884615385 8009.1346153846 0.0))
((0 . "LINE") (100 . "AcDbEntity") (8 . "SOLAR") (62 . 7) (370 . 13) (100 . "AcDbLine") (10 5910.2884615385
8009.1346153846 0.0) (11 5935.1131221719 7975.2828054299 0.0))
((0 . "LINE") (100 . "AcDbEntity") (8 . "SOLAR") (62 . 7) (370 . 13) (100 . "AcDbLine") (10 5935.1131221719
7975.2828054299 0.0) (11 5959.9377828054 7941.4309954751 0.0))
((0 . "LINE") (100 . "AcDbEntity") (8 . "SOLAR") (62 . 7) (370 . 13) (100 . "AcDbLine") (10 5959.9377828054
7941.4309954751 0.0) (11 5985.0113122172 7907.2398190045 0.0))
((0 . "LINE") (100 . "AcDbEntity") (8 . "SOLAR") (62 . 7) (370 . 13) (100 . "AcDbLine") (10 5985.0113122172
7907.2398190045 0.0) (11 5744.3438914027 7907.2398190045 0.0))
((0 . "LINE") (100 . "AcDbEntity") (8 . "SOLAR") (62 . 7) (370 . 13) (100 . "AcDbLine") (10 5744.3438914027
7907.2398190045 0.0) (11 5484.1628959276 7907.2398190045 0.0))
((0 . "LINE") (100 . "AcDbEntity") (8 . "SOLAR") (62 . 7) (370 . 13) (100 . "AcDbLine") (10 5484.1628959276
7907.2398190045 0.0) (11 5243.4954751131 7907.2398190045 0.0))
((0 . "LINE") (100 . "AcDbEntity") (8 . "SOLAR") (62 . 7) (370 . 13) (100 . "AcDbLine") (10 5243.4954751131
7907.2398190045 0.0) (11 5218.4219457014 7941.4309954751 0.0))
((0 . "LINE") (100 . "AcDbEntity") (8 . "SOLAR") (62 . 7) (370 . 13) (100 . "AcDbLine") (10 5218.4219457014
7941.4309954751 0.0) (11 5193.5972850679 7975.2828054299 0.0))
((0 . "LINE") (100 . "AcDbEntity") (8 . "SOLAR") (62 . 7) (370 . 13) (100 . "AcDbLine") (10 5193.5972850679
7975.2828054299 0.0) (11 5168.7726244344 8009.1346153846 0.0))
((0 . "LINE") (100 . "AcDbEntity") (8 . "SOLAR") (62 . 7) (370 . 13) (100 . "AcDbLine") (10 5168.7726244344
8009.1346153846 0.0) (11 5129.7624434389 8062.3303167421 0.0))
((0 . "LINE") (100 . "AcDbEntity") (8 . "SOLAR") (62 . 7) (370 . 13) (100 . "AcDbLine") (10 5129.7624434389
8062.3303167421 0.0) (11 5095.4807692308 8109.0780542986 0.0))
((0 . "LINE") (100 . "AcDbEntity") (8 . "SOLAR") (62 . 7) (370 . 13) (100 . "AcDbLine") (10 5095.4807692308
8109.0780542986 0.0) (11 5054.1063348416 8165.4977375566 0.0))
((0 . "LINE") (100 . "AcDbEntity") (8 . "SOLAR") (62 . 7) (370 . 13) (100 . "AcDbLine") (10 5054.1063348416
8165.4977375566 0.0) (11 5044.4004524887 8178.7330316742 0.0))
((0 . "LINE") (100 . "AcDbEntity") (8 . "SOLAR") (62 . 7) (370 . 13) (100 . "AcDbLine") (10 5285.0678733032
8178.7330316742 0.0) (11 5294.7737556561 8165.4977375566 0.0))
((0 . "LINE") (100 . "AcDbEntity") (8 . "SOLAR") (62 . 7) (370 . 13) (100 . "AcDbLine") (10 5294.7737556561
8165.4977375566 0.0) (11 5336.1481900452 8109.0780542986 0.0))
((0 . "LINE") (100 . "AcDbEntity") (8 . "SOLAR") (62 . 7) (370 . 13) (100 . "AcDbLine") (10 5336.1481900452
8109.0780542986 0.0) (11 5370.4298642534 8062.3303167421 0.0))
((0 . "LINE") (100 . "AcDbEntity") (8 . "SOLAR") (62 . 7) (370 . 13) (100 . "AcDbLine") (10 5370.4298642534
8062.3303167421 0.0) (11 5409.4400452489 8009.1346153846 0.0))
((0 . "LINE") (100 . "AcDbEntity") (8 . "SOLAR") (62 . 7) (370 . 13) (100 . "AcDbLine") (10 5409.4400452489
8009.1346153846 0.0) (11 5434.2647058824 7975.2828054299 0.0))
((0 . "LINE") (100 . "AcDbEntity") (8 . "SOLAR") (62 . 7) (370 . 13) (100 . "AcDbLine") (10 5434.2647058824
7975.2828054299 0.0) (11 5459.0893665158 7941.4309954751 0.0))
((0 . "LINE") (100 . "AcDbEntity") (8 . "SOLAR") (62 . 7) (370 . 13) (100 . "AcDbLine") (10 5459.0893665158
7941.4309954751 0.0) (11 5484.1628959276 7907.2398190045 0.0))
((0 . "LINE") (100 . "AcDbEntity") (8 . "SOLAR") (62 . 7) (370 . 13) (100 . "AcDbLine") (10 5545.2488687783
8178.7330316742 0.0) (11 5554.9547511312 8165.4977375566 0.0))
((0 . "LINE") (100 . "AcDbEntity") (8 . "SOLAR") (62 . 7) (370 . 13) (100 . "AcDbLine") (10 5554.9547511312
8165.4977375566 0.0) (11 5596.3291855204 8109.0780542986 0.0))
((0 . "LINE") (100 . "AcDbEntity") (8 . "SOLAR") (62 . 7) (370 . 13) (100 . "AcDbLine") (10 5596.3291855204
8109.0780542986 0.0) (11 5630.6108597285 8062.3303167421 0.0))
((0 . "LINE") (100 . "AcDbEntity") (8 . "SOLAR") (62 . 7) (370 . 13) (100 . "AcDbLine") (10 5630.6108597285
8062.3303167421 0.0) (11 5669.621040724 8009.1346153846 0.0))
((0 . "LINE") (100 . "AcDbEntity") (8 . "SOLAR") (62 . 7) (370 . 13) (100 . "AcDbLine") (10 5669.621040724
8009.1346153846 0.0) (11 5694.4457013575 7975.2828054299 0.0))
((0 . "LINE") (100 . "AcDbEntity") (8 . "SOLAR") (62 . 7) (370 . 13) (100 . "AcDbLine") (10 5694.4457013575
7975.2828054299 0.0) (11 5719.270361991 7941.4309954751 0.0))
((0 . "LINE") (100 . "AcDbEntity") (8 . "SOLAR") (62 . 7) (370 . 13) (100 . "AcDbLine") (10 5719.270361991
7941.4309954751 0.0) (11 5744.3438914027 7907.2398190045 0.0))
((0 . "LINE") (100 . "AcDbEntity") (8 . "SOLAR") (62 . 7) (370 . 13) (100 . "AcDbLine") (10 5054.1063348416
8165.4977375566 0.0) (11 5294.7737556561 8165.4977375566 0.0))
((0 . "LINE") (100 . "AcDbEntity") (8 . "SOLAR") (62 . 7) (370 . 13) (100 . "AcDbLine") (10 5294.7737556561
8165.4977375566 0.0) (11 5554.9547511312 8165.4977375566 0.0))
((0 . "LINE") (100 . "AcDbEntity") (8 . "SOLAR") (62 . 7) (370 . 13) (100 . "AcDbLine") (10 5554.9547511312
8165.4977375566 0.0) (11 5795.6221719457 8165.4977375566 0.0))
((0 . "LINE") (100 . "AcDbEntity") (8 . "SOLAR") (62 . 7) (370 . 13) (100 . "AcDbLine") (10 5095.4807692308
8109.0780542986 0.0) (11 5336.1481900452 8109.0780542986 0.0))
((0 . "LINE") (100 . "AcDbEntity") (8 . "SOLAR") (62 . 7) (370 . 13) (100 . "AcDbLine") (10 5336.1481900452
8109.0780542986 0.0) (11 5596.3291855204 8109.0780542986 0.0))
((0 . "LINE") (100 . "AcDbEntity") (8 . "SOLAR") (62 . 7) (370 . 13) (100 . "AcDbLine") (10 5596.3291855204
8109.0780542986 0.0) (11 5836.9966063348 8109.0780542986 0.0))
((0 . "LINE") (100 . "AcDbEntity") (8 . "SOLAR") (62 . 7) (370 . 13) (100 . "AcDbLine") (10 5129.7624434389
8062.3303167421 0.0) (11 5370.4298642534 8062.3303167421 0.0))
((0 . "LINE") (100 . "AcDbEntity") (8 . "SOLAR") (62 . 7) (370 . 13) (100 . "AcDbLine") (10 5370.4298642534
8062.3303167421 0.0) (11 5630.6108597285 8062.3303167421 0.0))
((0 . "LINE") (100 . "AcDbEntity") (8 . "SOLAR") (62 . 7) (370 . 13) (100 . "AcDbLine") (10 5630.6108597285
8062.3303167421 0.0) (11 5871.278280543 8062.3303167421 0.0))
((0 . "LINE") (100 . "AcDbEntity") (8 . "SOLAR") (62 . 7) (370 . 13) (100 . "AcDbLine") (10 5168.7726244344
8009.1346153846 0.0) (11 5409.4400452489 8009.1346153846 0.0))
((0 . "LINE") (100 . "AcDbEntity") (8 . "SOLAR") (62 . 7) (370 . 13) (100 . "AcDbLine") (10 5409.4400452489
8009.1346153846 0.0) (11 5669.621040724 8009.1346153846 0.0))
((0 . "LINE") (100 . "AcDbEntity") (8 . "SOLAR") (62 . 7) (370 . 13) (100 . "AcDbLine") (10 5669.621040724
8009.1346153846 0.0) (11 5910.2884615385 8009.1346153846 0.0))
((0 . "LINE") (100 . "AcDbEntity") (8 . "SOLAR") (62 . 7) (370 . 13) (100 . "AcDbLine") (10 5193.5972850679
7975.2828054299 0.0) (11 5434.2647058824 7975.2828054299 0.0))
((0 . "LINE") (100 . "AcDbEntity") (8 . "SOLAR") (62 . 7) (370 . 13) (100 . "AcDbLine") (10 5434.2647058824
7975.2828054299 0.0) (11 5694.4457013575 7975.2828054299 0.0))
((0 . "LINE") (100 . "AcDbEntity") (8 . "SOLAR") (62 . 7) (370 . 13) (100 . "AcDbLine") (10 5694.4457013575
7975.2828054299 0.0) (11 5935.1131221719 7975.2828054299 0.0))
((0 . "LINE") (100 . "AcDbEntity") (8 . "SOLAR") (62 . 7) (370 . 13) (100 . "AcDbLine") (10 5218.4219457014
7941.4309954751 0.0) (11 5459.0893665158 7941.4309954751 0.0))
((0 . "LINE") (100 . "AcDbEntity") (8 . "SOLAR") (62 . 7) (370 . 13) (100 . "AcDbLine") (10 5459.0893665158
7941.4309954751 0.0) (11 5719.270361991 7941.4309954751 0.0))
((0 . "LINE") (100 . "AcDbEntity") (8 . "SOLAR") (62 . 7) (370 . 13) (100 . "AcDbLine") (10 5719.270361991
7941.4309954751 0.0) (11 5959.9377828054 7941.4309954751 0.0))
((0 . "LINE") (100 . "AcDbEntity") (8 . "SOLAR") (62 . 7) (370 . 13) (100 . "AcDbLine") (10 5814.4796380091
8212.6696832579 0.0) (11 6606.334841629 8212.6696832579 0.0))
((0 . "LINE") (100 . "AcDbEntity") (8 . "SOLAR") (62 . 7) (370 . 13) (100 . "AcDbLine") (10 6606.334841629
8212.6696832579 0.0) (11 6843.8914027149 7873.3031674208 0.0))
((0 . "LINE") (100 . "AcDbEntity") (8 . "SOLAR") (62 . 7) (370 . 13) (100 . "AcDbLine") (10 6843.8914027149
7873.3031674208 0.0) (11 6063.3484162896 7873.3031674208 0.0))
((0 . "LINE") (100 . "AcDbEntity") (8 . "SOLAR") (62 . 7) (370 . 13) (100 . "AcDbLine") (10 6063.3484162896
7873.3031674208 0.0) (11 5814.4796380091 8212.6696832579 0.0))
((0 . "LINE") (100 . "AcDbEntity") (8 . "SOLAR") (62 . 7) (370 . 13) (100 . "AcDbLine") (10 5859.1346153846
8178.7330316742 0.0) (11 6102.9411764706 8178.7330316742 0.0))
((0 . "LINE") (100 . "AcDbEntity") (8 . "SOLAR") (62 . 7) (370 . 13) (100 . "AcDbLine") (10 6102.9411764706
8178.7330316742 0.0) (11 6366.5158371041 8178.7330316742 0.0))
((0 . "LINE") (100 . "AcDbEntity") (8 . "SOLAR") (62 . 7) (370 . 13) (100 . "AcDbLine") (10 6366.5158371041
8178.7330316742 0.0) (11 6610.32239819 8178.7330316742 0.0))
((0 . "LINE") (100 . "AcDbEntity") (8 . "SOLAR") (62 . 7) (370 . 13) (100 . "AcDbLine") (10 6610.32239819
8178.7330316742 0.0) (11 6619.5981334842 8165.4977375566 0.0))
((0 . "LINE") (100 . "AcDbEntity") (8 . "SOLAR") (62 . 7) (370 . 13) (100 . "AcDbLine") (10 6619.5981334842
8165.4977375566 0.0) (11 6659.1389253394 8109.0780542986 0.0))
((0 . "LINE") (100 . "AcDbEntity") (8 . "SOLAR") (62 . 7) (370 . 13) (100 . "AcDbLine") (10 6659.1389253394
8109.0780542986 0.0) (11 6690.771561086 8063.9423076923 0.0))
((0 . "LINE") (100 . "AcDbEntity") (8 . "SOLAR") (62 . 7) (370 . 13) (100 . "AcDbLine") (10 6690.771561086
8063.9423076923 0.0) (11 6729.1826244344 8009.1346153846 0.0))
((0 . "LINE") (100 . "AcDbEntity") (8 . "SOLAR") (62 . 7) (370 . 13) (100 . "AcDbLine") (10 6729.1826244344
8009.1346153846 0.0) (11 6752.9071040724 7975.2828054299 0.0))
((0 . "LINE") (100 . "AcDbEntity") (8 . "SOLAR") (62 . 7) (370 . 13) (100 . "AcDbLine") (10 6752.9071040724
7975.2828054299 0.0) (11 6776.6315723982 7941.4309954751 0.0))
((0 . "LINE") (100 . "AcDbEntity") (8 . "SOLAR") (62 . 7) (370 . 13) (100 . "AcDbLine") (10 6776.6315723982
7941.4309954751 0.0) (11 6800.5938914027 7907.2398190045 0.0))
((0 . "LINE") (100 . "AcDbEntity") (8 . "SOLAR") (62 . 7) (370 . 13) (100 . "AcDbLine") (10 6800.5938914027
7907.2398190045 0.0) (11 6559.5776809955 7907.2398190045 0.0))
((0 . "LINE") (100 . "AcDbEntity") (8 . "SOLAR") (62 . 7) (370 . 13) (100 . "AcDbLine") (10 6559.5776809955
7907.2398190045 0.0) (11 6299.0196040724 7907.2398190045 0.0))
((0 . "LINE") (100 . "AcDbEntity") (8 . "SOLAR") (62 . 7) (370 . 13) (100 . "AcDbLine") (10 6299.0196040724
7907.2398190045 0.0) (11 6058.0033936652 7907.2398190045 0.0))
((0 . "LINE") (100 . "AcDbEntity") (8 . "SOLAR") (62 . 7) (370 . 13) (100 . "AcDbLine") (10 6058.0033936652
7907.2398190045 0.0) (11 6032.9583597285 7941.4309954751 0.0))
((0 . "LINE") (100 . "AcDbEntity") (8 . "SOLAR") (62 . 7) (370 . 13) (100 . "AcDbLine") (10 6032.9583597285
7941.4309954751 0.0) (11 6008.1619117647 7975.2828054299 0.0))
((0 . "LINE") (100 . "AcDbEntity") (8 . "SOLAR") (62 . 7) (370 . 13) (100 . "AcDbLine") (10 6008.1619117647
7975.2828054299 0.0) (11 5983.3654524887 8009.1346153846 0.0))
((0 . "LINE") (100 . "AcDbEntity") (8 . "SOLAR") (62 . 7) (370 . 13) (100 . "AcDbLine") (10 5983.3654524887
8009.1346153846 0.0) (11 5943.2188235294 8063.9423076923 0.0))
((0 . "LINE") (100 . "AcDbEntity") (8 . "SOLAR") (62 . 7) (370 . 13) (100 . "AcDbLine") (10 5943.2188235294
8063.9423076923 0.0) (11 5910.1568891403 8109.0780542986 0.0))
((0 . "LINE") (100 . "AcDbEntity") (8 . "SOLAR") (62 . 7) (370 . 13) (100 . "AcDbLine") (10 5910.1568891403
8109.0780542986 0.0) (11 5868.8294683258 8165.4977375566 0.0))
((0 . "LINE") (100 . "AcDbEntity") (8 . "SOLAR") (62 . 7) (370 . 13) (100 . "AcDbLine") (10 5868.8294683258
8165.4977375566 0.0) (11 5859.1346153846 8178.7330316742 0.0))
((0 . "LINE") (100 . "AcDbEntity") (8 . "SOLAR") (62 . 7) (370 . 13) (100 . "AcDbLine") (10 6102.9411764706
8178.7330316742 0.0) (11 6112.5 8165.4977375566 0.0))
((0 . "LINE") (100 . "AcDbEntity") (8 . "SOLAR") (62 . 7) (370 . 13) (100 . "AcDbLine") (10 6112.5 8165.4977375566 0.0)
(11 6153.2475452489 8109.0780542986 0.0))
((0 . "LINE") (100 . "AcDbEntity") (8 . "SOLAR") (62 . 7) (370 . 13) (100 . "AcDbLine") (10 6153.2475452489
8109.0780542986 0.0) (11 6185.8455882353 8063.9423076923 0.0))
((0 . "LINE") (100 . "AcDbEntity") (8 . "SOLAR") (62 . 7) (370 . 13) (100 . "AcDbLine") (10 6185.8455882353
8063.9423076923 0.0) (11 6225.4289253394 8009.1346153846 0.0))
((0 . "LINE") (100 . "AcDbEntity") (8 . "SOLAR") (62 . 7) (370 . 13) (100 . "AcDbLine") (10 6225.4289253394
8009.1346153846 0.0) (11 6249.8774547511 7975.2828054299 0.0))
((0 . "LINE") (100 . "AcDbEntity") (8 . "SOLAR") (62 . 7) (370 . 13) (100 . "AcDbLine") (10 6249.8774547511
7975.2828054299 0.0) (11 6274.3259841629 7941.4309954751 0.0))
((0 . "LINE") (100 . "AcDbEntity") (8 . "SOLAR") (62 . 7) (370 . 13) (100 . "AcDbLine") (10 6274.3259841629
7941.4309954751 0.0) (11 6299.0196040724 7907.2398190045 0.0))
((0 . "LINE") (100 . "AcDbEntity") (8 . "SOLAR") (62 . 7) (370 . 13) (100 . "AcDbLine") (10 6366.5158371041
8178.7330316742 0.0) (11 6375.92760181 8165.4977375566 0.0))
((0 . "LINE") (100 . "AcDbEntity") (8 . "SOLAR") (62 . 7) (370 . 13) (100 . "AcDbLine") (10 6375.92760181
8165.4977375566 0.0) (11 6416.0482692308 8109.0780542986 0.0))
((0 . "LINE") (100 . "AcDbEntity") (8 . "SOLAR") (62 . 7) (370 . 13) (100 . "AcDbLine") (10 6416.0482692308
8109.0780542986 0.0) (11 6448.1447963801 8063.9423076923 0.0))
((0 . "LINE") (100 . "AcDbEntity") (8 . "SOLAR") (62 . 7) (370 . 13) (100 . "AcDbLine") (10 6448.1447963801
8063.9423076923 0.0) (11 6487.1191515837 8009.1346153846 0.0))
((0 . "LINE") (100 . "AcDbEntity") (8 . "SOLAR") (62 . 7) (370 . 13) (100 . "AcDbLine") (10 6487.1191515837
8009.1346153846 0.0) (11 6511.1915497738 7975.2828054299 0.0))
((0 . "LINE") (100 . "AcDbEntity") (8 . "SOLAR") (62 . 7) (370 . 13) (100 . "AcDbLine") (10 6511.1915497738
7975.2828054299 0.0) (11 6535.2639479638 7941.4309954751 0.0))
((0 . "LINE") (100 . "AcDbEntity") (8 . "SOLAR") (62 . 7) (370 . 13) (100 . "AcDbLine") (10 6535.2639479638
7941.4309954751 0.0) (11 6559.5776809955 7907.2398190045 0.0))
((0 . "LINE") (100 . "AcDbEntity") (8 . "SOLAR") (62 . 7) (370 . 13) (100 . "AcDbLine") (10 5868.8294683258
8165.4977375566 0.0) (11 6112.5 8165.4977375566 0.0))
((0 . "LINE") (100 . "AcDbEntity") (8 . "SOLAR") (62 . 7) (370 . 13) (100 . "AcDbLine") (10 6112.5 8165.4977375566 0.0)
(11 6375.92760181 8165.4977375566 0.0))
((0 . "LINE") (100 . "AcDbEntity") (8 . "SOLAR") (62 . 7) (370 . 13) (100 . "AcDbLine") (10 6375.92760181
8165.4977375566 0.0) (11 6619.5981334842 8165.4977375566 0.0))
((0 . "LINE") (100 . "AcDbEntity") (8 . "SOLAR") (62 . 7) (370 . 13) (100 . "AcDbLine") (10 5910.1568891403
8109.0780542986 0.0) (11 6153.2475452489 8109.0780542986 0.0))
((0 . "LINE") (100 . "AcDbEntity") (8 . "SOLAR") (62 . 7) (370 . 13) (100 . "AcDbLine") (10 6153.2475452489
8109.0780542986 0.0) (11 6416.0482692308 8109.0780542986 0.0))
((0 . "LINE") (100 . "AcDbEntity") (8 . "SOLAR") (62 . 7) (370 . 13) (100 . "AcDbLine") (10 6416.0482692308
8109.0780542986 0.0) (11 6659.1389253394 8109.0780542986 0.0))
((0 . "LINE") (100 . "AcDbEntity") (8 . "SOLAR") (62 . 7) (370 . 13) (100 . "AcDbLine") (10 5943.2188235294
8063.9423076923 0.0) (11 6185.8455882353 8063.9423076923 0.0))
((0 . "LINE") (100 . "AcDbEntity") (8 . "SOLAR") (62 . 7) (370 . 13) (100 . "AcDbLine") (10 6185.8455882353
8063.9423076923 0.0) (11 6448.1447963801 8063.9423076923 0.0))
((0 . "LINE") (100 . "AcDbEntity") (8 . "SOLAR") (62 . 7) (370 . 13) (100 . "AcDbLine") (10 6448.1447963801
8063.9423076923 0.0) (11 6690.771561086 8063.9423076923 0.0))
((0 . "LINE") (100 . "AcDbEntity") (8 . "SOLAR") (62 . 7) (370 . 13) (100 . "AcDbLine") (10 5983.3654524887
8009.1346153846 0.0) (11 6225.4289253394 8009.1346153846 0.0))
((0 . "LINE") (100 . "AcDbEntity") (8 . "SOLAR") (62 . 7) (370 . 13) (100 . "AcDbLine") (10 6225.4289253394
8009.1346153846 0.0) (11 6487.1191515837 8009.1346153846 0.0))
((0 . "LINE") (100 . "AcDbEntity") (8 . "SOLAR") (62 . 7) (370 . 13) (100 . "AcDbLine") (10 6487.1191515837
8009.1346153846 0.0) (11 6729.1826244344 8009.1346153846 0.0))
((0 . "LINE") (100 . "AcDbEntity") (8 . "SOLAR") (62 . 7) (370 . 13) (100 . "AcDbLine") (10 6008.1619117647
7975.2828054299 0.0) (11 6249.8774547511 7975.2828054299 0.0))
((0 . "LINE") (100 . "AcDbEntity") (8 . "SOLAR") (62 . 7) (370 . 13) (100 . "AcDbLine") (10 6249.8774547511
7975.2828054299 0.0) (11 6511.1915497738 7975.2828054299 0.0))
((0 . "LINE") (100 . "AcDbEntity") (8 . "SOLAR") (62 . 7) (370 . 13) (100 . "AcDbLine") (10 6511.1915497738
7975.2828054299 0.0) (11 6752.9071040724 7975.2828054299 0.0))
((0 . "LINE") (100 . "AcDbEntity") (8 . "SOLAR") (62 . 7) (370 . 13) (100 . "AcDbLine") (10 6032.9583597285
7941.4309954751 0.0) (11 6274.3259841629 7941.4309954751 0.0))
((0 . "LINE") (100 . "AcDbEntity") (8 . "SOLAR") (62 . 7) (370 . 13) (100 . "AcDbLine") (10 6274.3259841629
7941.4309954751 0.0) (11 6535.2639479638 7941.4309954751 0.0))
((0 . "LINE") (100 . "AcDbEntity") (8 . "SOLAR") (62 . 7) (370 . 13) (100 . "AcDbLine") (10 6535.2639479638
7941.4309954751 0.0) (11 6776.6315723982 7941.4309954751 0.0))
((0 . "LINE") (100 . "AcDbEntity") (8 . "SOLAR") (62 . 7) (370 . 13) (100 . "AcDbLine") (10 6640.2714932127
8212.6696832579 0.0) (11 7330.3167420814 8212.6696832579 0.0))
((0 . "LINE") (100 . "AcDbEntity") (8 . "SOLAR") (62 . 7) (370 . 13) (100 . "AcDbLine") (10 7330.3167420814
8212.6696832579 0.0) (11 7545.2488687783 7873.3031674208 0.0))
((0 . "LINE") (100 . "AcDbEntity") (8 . "SOLAR") (62 . 7) (370 . 13) (100 . "AcDbLine") (10 7545.2488687783
7873.3031674208 0.0) (11 6889.1402714932 7873.3031674208 0.0))
((0 . "LINE") (100 . "AcDbEntity") (8 . "SOLAR") (62 . 7) (370 . 13) (100 . "AcDbLine") (10 6889.1402714932
7873.3031674208 0.0) (11 6640.2714932127 8212.6696832579 0.0))
((0 . "LINE") (100 . "AcDbEntity") (8 . "SOLAR") (62 . 7) (370 . 13) (100 . "AcDbLine") (10 6682.3246606335
8178.7330316742 0.0) (11 6894.0422285068 8178.7330316742 0.0))
((0 . "LINE") (100 . "AcDbEntity") (8 . "SOLAR") (62 . 7) (370 . 13) (100 . "AcDbLine") (10 6894.0422285068
8178.7330316742 0.0) (11 7122.9260972851 8178.7330316742 0.0))
((0 . "LINE") (100 . "AcDbEntity") (8 . "SOLAR") (62 . 7) (370 . 13) (100 . "AcDbLine") (10 7122.9260972851
8178.7330316742 0.0) (11 7334.6436651584 8178.7330316742 0.0))
((0 . "LINE") (100 . "AcDbEntity") (8 . "SOLAR") (62 . 7) (370 . 13) (100 . "AcDbLine") (10 7334.6436651584
8178.7330316742 0.0) (11 7343.0591063348 8165.4977375566 0.0))
((0 . "LINE") (100 . "AcDbEntity") (8 . "SOLAR") (62 . 7) (370 . 13) (100 . "AcDbLine") (10 7343.0591063348
8165.4977375566 0.0) (11 7382.0075 8104.242081448 0.0))
((0 . "LINE") (100 . "AcDbEntity") (8 . "SOLAR") (62 . 7) (370 . 13) (100 . "AcDbLine") (10 7382.0075 8104.242081448
0.0) (11 7407.6314366516 8063.9423076923 0.0))
((0 . "LINE") (100 . "AcDbEntity") (8 . "SOLAR") (62 . 7) (370 . 13) (100 . "AcDbLine") (10 7407.6314366516
8063.9423076923 0.0) (11 7442.4799886878 8009.1346153846 0.0))
((0 . "LINE") (100 . "AcDbEntity") (8 . "SOLAR") (62 . 7) (370 . 13) (100 . "AcDbLine") (10 7442.4799886878
8009.1346153846 0.0) (11 7464.0040950226 7975.2828054299 0.0))
((0 . "LINE") (100 . "AcDbEntity") (8 . "SOLAR") (62 . 7) (370 . 13) (100 . "AcDbLine") (10 7464.0041063348
7975.2828054299 0.0) (11 7485.5282126697 7941.4309954751 0.0))
((0 . "LINE") (100 . "AcDbEntity") (8 . "SOLAR") (62 . 7) (370 . 13) (100 . "AcDbLine") (10 7485.5282126697
7941.4309954751 0.0) (11 7507.2680995475 7907.2398190045 0.0))
((0 . "LINE") (100 . "AcDbEntity") (8 . "SOLAR") (62 . 7) (370 . 13) (100 . "AcDbLine") (10 7507.2680995475
7907.2398190045 0.0) (11 7303.9215723982 7907.2398190045 0.0))
((0 . "LINE") (100 . "AcDbEntity") (8 . "SOLAR") (62 . 7) (370 . 13) (100 . "AcDbLine") (10 7303.9215723982
7907.2398190045 0.0) (11 7084.0874773756 7907.2398190045 0.0))
((0 . "LINE") (100 . "AcDbEntity") (8 . "SOLAR") (62 . 7) (370 . 13) (100 . "AcDbLine") (10 7084.0874773756
7907.2398190045 0.0) (11 6880.7409502262 7907.2398190045 0.0))
((0 . "LINE") (100 . "AcDbEntity") (8 . "SOLAR") (62 . 7) (370 . 13) (100 . "AcDbLine") (10 6880.7409502262
7907.2398190045 0.0) (11 6855.7528959276 7941.4309954751 0.0))
((0 . "LINE") (100 . "AcDbEntity") (8 . "SOLAR") (62 . 7) (370 . 13) (100 . "AcDbLine") (10 6855.7528959276
7941.4309954751 0.0) (11 6831.0128733032 7975.2828054299 0.0))
((0 . "LINE") (100 . "AcDbEntity") (8 . "SOLAR") (62 . 7) (370 . 13) (100 . "AcDbLine") (10 6831.0128733032
7975.2828054299 0.0) (11 6806.2728393665 8009.1346153846 0.0))
((0 . "LINE") (100 . "AcDbEntity") (8 . "SOLAR") (62 . 7) (370 . 13) (100 . "AcDbLine") (10 6806.2728393665
8009.1346153846 0.0) (11 6766.2175452489 8063.9423076923 0.0))
((0 . "LINE") (100 . "AcDbEntity") (8 . "SOLAR") (62 . 7) (370 . 13) (100 . "AcDbLine") (10 6766.2175452489
8063.9423076923 0.0) (11 6736.7651357466 8104.242081448 0.0))
((0 . "LINE") (100 . "AcDbEntity") (8 . "SOLAR") (62 . 7) (370 . 13) (100 . "AcDbLine") (10 6736.7651357466
8104.242081448 0.0) (11 6691.9974547511 8165.4977375566 0.0))
((0 . "LINE") (100 . "AcDbEntity") (8 . "SOLAR") (62 . 7) (370 . 13) (100 . "AcDbLine") (10 6691.9974547511
8165.4977375566 0.0) (11 6682.3246606335 8178.7330316742 0.0))
((0 . "LINE") (100 . "AcDbEntity") (8 . "SOLAR") (62 . 7) (370 . 13) (100 . "AcDbLine") (10 6894.0422285068
8178.7330316742 0.0) (11 6903.3069343891 8165.4977375566 0.0))
((0 . "LINE") (100 . "AcDbEntity") (8 . "SOLAR") (62 . 7) (370 . 13) (100 . "AcDbLine") (10 6903.3069343891
8165.4977375566 0.0) (11 6946.1858936652 8104.242081448 0.0))
((0 . "LINE") (100 . "AcDbEntity") (8 . "SOLAR") (62 . 7) (370 . 13) (100 . "AcDbLine") (10 6946.1858936652
8104.242081448 0.0) (11 6974.3957352941 8063.9423076923 0.0))
((0 . "LINE") (100 . "AcDbEntity") (8 . "SOLAR") (62 . 7) (370 . 13) (100 . "AcDbLine") (10 6974.3957352941
8063.9423076923 0.0) (11 7012.7611199095 8009.1346153846 0.0))
((0 . "LINE") (100 . "AcDbEntity") (8 . "SOLAR") (62 . 7) (370 . 13) (100 . "AcDbLine") (10 7012.7611199095
8009.1346153846 0.0) (11 7036.4573868778 7975.2828054299 0.0))
((0 . "LINE") (100 . "AcDbEntity") (8 . "SOLAR") (62 . 7) (370 . 13) (100 . "AcDbLine") (10 7036.4573868778
7975.2828054299 0.0) (11 7060.1536538462 7941.4309954751 0.0))
((0 . "LINE") (100 . "AcDbEntity") (8 . "SOLAR") (62 . 7) (370 . 13) (100 . "AcDbLine") (10 7060.1536538462
7941.4309954751 0.0) (11 7084.0874773756 7907.2398190045 0.0))
((0 . "LINE") (100 . "AcDbEntity") (8 . "SOLAR") (62 . 7) (370 . 13) (100 . "AcDbLine") (10 7122.9260972851
8178.7330316742 0.0) (11 7131.7496266968 8165.4977375566 0.0))
((0 . "LINE") (100 . "AcDbEntity") (8 . "SOLAR") (62 . 7) (370 . 13) (100 . "AcDbLine") (10 7131.7496266968
8165.4977375566 0.0) (11 7172.5867307692 8104.242081448 0.0))
((0 . "LINE") (100 . "AcDbEntity") (8 . "SOLAR") (62 . 7) (370 . 13) (100 . "AcDbLine") (10 7172.5867307692
8104.242081448 0.0) (11 7199.4532466063 8063.9423076923 0.0))
((0 . "LINE") (100 . "AcDbEntity") (8 . "SOLAR") (62 . 7) (370 . 13) (100 . "AcDbLine") (10 7199.4532466063
8063.9423076923 0.0) (11 7235.9917081448 8009.1346153846 0.0))
((0 . "LINE") (100 . "AcDbEntity") (8 . "SOLAR") (62 . 7) (370 . 13) (100 . "AcDbLine") (10 7235.9917081448
8009.1346153846 0.0) (11 7258.559581448 7975.2828054299 0.0))
((0 . "LINE") (100 . "AcDbEntity") (8 . "SOLAR") (62 . 7) (370 . 13) (100 . "AcDbLine") (10 7258.559581448
7975.2828054299 0.0) (11 7281.1274547511 7941.4309954751 0.0))
((0 . "LINE") (100 . "AcDbEntity") (8 . "SOLAR") (62 . 7) (370 . 13) (100 . "AcDbLine") (10 7281.1274547511
7941.4309954751 0.0) (11 7303.9215723982 7907.2398190045 0.0))
((0 . "LINE") (100 . "AcDbEntity") (8 . "SOLAR") (62 . 7) (370 . 13) (100 . "AcDbLine") (10 6691.9974547511
8165.4977375566 0.0) (11 6903.3069343891 8165.4977375566 0.0))
((0 . "LINE") (100 . "AcDbEntity") (8 . "SOLAR") (62 . 7) (370 . 13) (100 . "AcDbLine") (10 6903.3069343891
8165.4977375566 0.0) (11 7131.7496266968 8165.4977375566 0.0))
((0 . "LINE") (100 . "AcDbEntity") (8 . "SOLAR") (62 . 7) (370 . 13) (100 . "AcDbLine") (10 7131.7496266968
8165.4977375566 0.0) (11 7343.0591063348 8165.4977375566 0.0))
((0 . "LINE") (100 . "AcDbEntity") (8 . "SOLAR") (62 . 7) (370 . 13) (100 . "AcDbLine") (10 6736.7651357466
8104.242081448 0.0) (11 6946.1858936652 8104.242081448 0.0))
((0 . "LINE") (100 . "AcDbEntity") (8 . "SOLAR") (62 . 7) (370 . 13) (100 . "AcDbLine") (10 6946.1858936652
8104.242081448 0.0) (11 7172.5867307692 8104.242081448 0.0))
((0 . "LINE") (100 . "AcDbEntity") (8 . "SOLAR") (62 . 7) (370 . 13) (100 . "AcDbLine") (10 7172.5867307692
8104.242081448 0.0) (11 7382.0075 8104.242081448 0.0))
((0 . "LINE") (100 . "AcDbEntity") (8 . "SOLAR") (62 . 7) (370 . 13) (100 . "AcDbLine") (10 6766.2175452489
8063.9423076923 0.0) (11 6974.3957352941 8063.9423076923 0.0))
((0 . "LINE") (100 . "AcDbEntity") (8 . "SOLAR") (62 . 7) (370 . 13) (100 . "AcDbLine") (10 6974.3957352941
8063.9423076923 0.0) (11 7199.4532466063 8063.9423076923 0.0))
((0 . "LINE") (100 . "AcDbEntity") (8 . "SOLAR") (62 . 7) (370 . 13) (100 . "AcDbLine") (10 7199.4532466063
8063.9423076923 0.0) (11 7407.6314366516 8063.9423076923 0.0))
((0 . "LINE") (100 . "AcDbEntity") (8 . "SOLAR") (62 . 7) (370 . 13) (100 . "AcDbLine") (10 6806.2728393665
8009.1346153846 0.0) (11 7012.7611199095 8009.1346153846 0.0))
((0 . "LINE") (100 . "AcDbEntity") (8 . "SOLAR") (62 . 7) (370 . 13) (100 . "AcDbLine") (10 7012.7611199095
8009.1346153846 0.0) (11 7235.9917081448 8009.1346153846 0.0))
((0 . "LINE") (100 . "AcDbEntity") (8 . "SOLAR") (62 . 7) (370 . 13) (100 . "AcDbLine") (10 7235.9917081448
8009.1346153846 0.0) (11 7442.4799886878 8009.1346153846 0.0))
((0 . "LINE") (100 . "AcDbEntity") (8 . "SOLAR") (62 . 7) (370 . 13) (100 . "AcDbLine") (10 6831.0128733032
7975.2828054299 0.0) (11 7036.4573868778 7975.2828054299 0.0))
((0 . "LINE") (100 . "AcDbEntity") (8 . "SOLAR") (62 . 7) (370 . 13) (100 . "AcDbLine") (10 7036.4573868778
7975.2828054299 0.0) (11 7258.559581448 7975.2828054299 0.0))
((0 . "LINE") (100 . "AcDbEntity") (8 . "SOLAR") (62 . 7) (370 . 13) (100 . "AcDbLine") (10 7258.559581448
7975.2828054299 0.0) (11 7464.0040950226 7975.2828054299 0.0))
((0 . "LINE") (100 . "AcDbEntity") (8 . "SOLAR") (62 . 7) (370 . 13) (100 . "AcDbLine") (10 6855.7528959276
7941.4309954751 0.0) (11 7060.1536538462 7941.4309954751 0.0))
((0 . "LINE") (100 . "AcDbEntity") (8 . "SOLAR") (62 . 7) (370 . 13) (100 . "AcDbLine") (10 7060.1536538462
7941.4309954751 0.0) (11 7281.1274547511 7941.4309954751 0.0))
((0 . "LINE") (100 . "AcDbEntity") (8 . "SOLAR") (62 . 7) (370 . 13) (100 . "AcDbLine") (10 7281.1274547511
7941.4309954751 0.0) (11 7485.5282126697 7941.4309954751 0.0))
((0 . "LINE") (100 . "AcDbEntity") (8 . "SOLAR") (62 . 7) (370 . 13) (100 . "AcDbLine") (10 7692.3076923077
8212.6696832579 0.0) (11 8518.0995475113 8212.6696832579 0.0))
((0 . "LINE") (100 . "AcDbEntity") (8 . "SOLAR") (62 . 7) (370 . 13) (100 . "AcDbLine") (10 8518.0995475113
8212.6696832579 0.0) (11 8733.0316742081 7873.3031674208 0.0))
((0 . "LINE") (100 . "AcDbEntity") (8 . "SOLAR") (62 . 7) (370 . 13) (100 . "AcDbLine") (10 8733.0316742081
7873.3031674208 0.0) (11 7895.92760181 7873.3031674208 0.0))
((0 . "LINE") (100 . "AcDbEntity") (8 . "SOLAR") (62 . 7) (370 . 13) (100 . "AcDbLine") (10 7895.92760181
7873.3031674208 0.0) (11 7692.3076923077 8212.6696832579 0.0))
((0 . "LINE") (100 . "AcDbEntity") (8 . "SOLAR") (62 . 7) (370 . 13) (100 . "AcDbLine") (10 7733.342760181
8178.7330316742 0.0) (11 7988.3107126697 8178.7330316742 0.0))
((0 . "LINE") (100 . "AcDbEntity") (8 . "SOLAR") (62 . 7) (370 . 13) (100 . "AcDbLine") (10 7988.3107126697
8178.7330316742 0.0) (11 8263.9517307692 8178.7330316742 0.0))
((0 . "LINE") (100 . "AcDbEntity") (8 . "SOLAR") (62 . 7) (370 . 13) (100 . "AcDbLine") (10 8263.9517307692
8178.7330316742 0.0) (11 8518.9196832579 8178.7330316742 0.0))
((0 . "LINE") (100 . "AcDbEntity") (8 . "SOLAR") (62 . 7) (370 . 13) (100 . "AcDbLine") (10 8518.9196832579
8178.7330316742 0.0) (11 8527.2910067873 8165.4977375566 0.0))
((0 . "LINE") (100 . "AcDbEntity") (8 . "SOLAR") (62 . 7) (370 . 13) (100 . "AcDbLine") (10 8527.2910067873
8165.4977375566 0.0) (11 8567.0547963801 8102.6300904977 0.0))
((0 . "LINE") (100 . "AcDbEntity") (8 . "SOLAR") (62 . 7) (370 . 13) (100 . "AcDbLine") (10 8567.0547963801
8102.6300904977 0.0) (11 8591.5248190045 8063.9423076923 0.0))
((0 . "LINE") (100 . "AcDbEntity") (8 . "SOLAR") (62 . 7) (370 . 13) (100 . "AcDbLine") (10 8591.5248190045
8063.9423076923 0.0) (11 8611.9165045249 8031.7024886878 0.0))
((0 . "LINE") (100 . "AcDbEntity") (8 . "SOLAR") (62 . 7) (370 . 13) (100 . "AcDbLine") (10 8611.9165045249
8031.7024886878 0.0) (11 8633.3277714932 7997.850678733 0.0))
((0 . "LINE") (100 . "AcDbEntity") (8 . "SOLAR") (62 . 7) (370 . 13) (100 . "AcDbLine") (10 8633.3277714932
7997.850678733 0.0) (11 8660.8565497738 7954.3269230769 0.0))
((0 . "LINE") (100 . "AcDbEntity") (8 . "SOLAR") (62 . 7) (370 . 13) (100 . "AcDbLine") (10 8660.8565497738
7954.3269230769 0.0) (11 8690.6391402715 7907.2398190045 0.0))
((0 . "LINE") (100 . "AcDbEntity") (8 . "SOLAR") (62 . 7) (370 . 13) (100 . "AcDbLine") (10 8690.6391402715
7907.2398190045 0.0) (11 8432.8808484163 7907.2398190045 0.0))
((0 . "LINE") (100 . "AcDbEntity") (8 . "SOLAR") (62 . 7) (370 . 13) (100 . "AcDbLine") (10 8432.8808484163
7907.2398190045 0.0) (11 8154.2232239819 7907.2398190045 0.0))
((0 . "LINE") (100 . "AcDbEntity") (8 . "SOLAR") (62 . 7) (370 . 13) (100 . "AcDbLine") (10 8154.2232239819
7907.2398190045 0.0) (11 7896.4649321267 7907.2398190045 0.0))
((0 . "LINE") (100 . "AcDbEntity") (8 . "SOLAR") (62 . 7) (370 . 13) (100 . "AcDbLine") (10 7896.4649321267
7907.2398190045 0.0) (11 7868.1734276018 7954.3269230769 0.0))
((0 . "LINE") (100 . "AcDbEntity") (8 . "SOLAR") (62 . 7) (370 . 13) (100 . "AcDbLine") (10 7868.1734276018
7954.3269230769 0.0) (11 7842.0229072398 7997.850678733 0.0))
((0 . "LINE") (100 . "AcDbEntity") (8 . "SOLAR") (62 . 7) (370 . 13) (100 . "AcDbLine") (10 7842.0229072398
7997.850678733 0.0) (11 7821.6836085973 8031.7024886878 0.0))
((0 . "LINE") (100 . "AcDbEntity") (8 . "SOLAR") (62 . 7) (370 . 13) (100 . "AcDbLine") (10 7821.6836085973
8031.7024886878 0.0) (11 7802.3128506787 8063.9423076923 0.0))
((0 . "LINE") (100 . "AcDbEntity") (8 . "SOLAR") (62 . 7) (370 . 13) (100 . "AcDbLine") (10 7802.3128506787
8063.9423076923 0.0) (11 7779.0679411765 8102.6300904977 0.0))
((0 . "LINE") (100 . "AcDbEntity") (8 . "SOLAR") (62 . 7) (370 . 13) (100 . "AcDbLine") (10 7779.0679411765
8102.6300904977 0.0) (11 7741.2949660633 8165.4977375566 0.0))
((0 . "LINE") (100 . "AcDbEntity") (8 . "SOLAR") (62 . 7) (370 . 13) (100 . "AcDbLine") (10 7741.2949660633
8165.4977375566 0.0) (11 7733.342760181 8178.7330316742 0.0))
((0 . "LINE") (100 . "AcDbEntity") (8 . "SOLAR") (62 . 7) (370 . 13) (100 . "AcDbLine") (10 7988.3107126697
8178.7330316742 0.0) (11 7996.3989479638 8165.4977375566 0.0))
((0 . "LINE") (100 . "AcDbEntity") (8 . "SOLAR") (62 . 7) (370 . 13) (100 . "AcDbLine") (10 7996.3989479638
8165.4977375566 0.0) (11 8034.8180656109 8102.6300904977 0.0))
((0 . "LINE") (100 . "AcDbEntity") (8 . "SOLAR") (62 . 7) (370 . 13) (100 . "AcDbLine") (10 8034.8180656109
8102.6300904977 0.0) (11 8058.4605995475 8063.9423076923 0.0))
((0 . "LINE") (100 . "AcDbEntity") (8 . "SOLAR") (62 . 7) (370 . 13) (100 . "AcDbLine") (10 8058.4605995475
8063.9423076923 0.0) (11 8078.1627036199 8031.7024886878 0.0))
((0 . "LINE") (100 . "AcDbEntity") (8 . "SOLAR") (62 . 7) (370 . 13) (100 . "AcDbLine") (10 8078.1627036199
8031.7024886878 0.0) (11 8098.8499208145 7997.850678733 0.0))
((0 . "LINE") (100 . "AcDbEntity") (8 . "SOLAR") (62 . 7) (370 . 13) (100 . "AcDbLine") (10 8098.8499208145
7997.850678733 0.0) (11 8125.4477714932 7954.3269230769 0.0))
((0 . "LINE") (100 . "AcDbEntity") (8 . "SOLAR") (62 . 7) (370 . 13) (100 . "AcDbLine") (10 8125.4477714932
7954.3269230769 0.0) (11 8154.2232239819 7907.2398190045 0.0))
((0 . "LINE") (100 . "AcDbEntity") (8 . "SOLAR") (62 . 7) (370 . 13) (100 . "AcDbLine") (10 8263.9517307692
8178.7330316742 0.0) (11 8272.1870248869 8165.4977375566 0.0))
((0 . "LINE") (100 . "AcDbEntity") (8 . "SOLAR") (62 . 7) (370 . 13) (100 . "AcDbLine") (10 8272.1870248869
8165.4977375566 0.0) (11 8311.3046719457 8102.6300904977 0.0))
((0 . "LINE") (100 . "AcDbEntity") (8 . "SOLAR") (62 . 7) (370 . 13) (100 . "AcDbLine") (10 8311.3046719457
8102.6300904977 0.0) (11 8335.3770701357 8063.9423076923 0.0))
((0 . "LINE") (100 . "AcDbEntity") (8 . "SOLAR") (62 . 7) (370 . 13) (100 . "AcDbLine") (10 8335.3770701357
8063.9423076923 0.0) (11 8355.4374095023 8031.7024886878 0.0))
((0 . "LINE") (100 . "AcDbEntity") (8 . "SOLAR") (62 . 7) (370 . 13) (100 . "AcDbLine") (10 8355.4374095023
8031.7024886878 0.0) (11 8376.5007579186 7997.850678733 0.0))
((0 . "LINE") (100 . "AcDbEntity") (8 . "SOLAR") (62 . 7) (370 . 13) (100 . "AcDbLine") (10 8376.5007579186
7997.850678733 0.0) (11 8403.5822058824 7954.3269230769 0.0))
((0 . "LINE") (100 . "AcDbEntity") (8 . "SOLAR") (62 . 7) (370 . 13) (100 . "AcDbLine") (10 8403.5822058824
7954.3269230769 0.0) (11 8432.8808484163 7907.2398190045 0.0))
((0 . "LINE") (100 . "AcDbEntity") (8 . "SOLAR") (62 . 7) (370 . 13) (100 . "AcDbLine") (10 7741.2949660633
8165.4977375566 0.0) (11 7996.3989479638 8165.4977375566 0.0))
((0 . "LINE") (100 . "AcDbEntity") (8 . "SOLAR") (62 . 7) (370 . 13) (100 . "AcDbLine") (10 7996.3989479638
8165.4977375566 0.0) (11 8272.1870248869 8165.4977375566 0.0))
((0 . "LINE") (100 . "AcDbEntity") (8 . "SOLAR") (62 . 7) (370 . 13) (100 . "AcDbLine") (10 8272.1870248869
8165.4977375566 0.0) (11 8527.2910067873 8165.4977375566 0.0))
((0 . "LINE") (100 . "AcDbEntity") (8 . "SOLAR") (62 . 7) (370 . 13) (100 . "AcDbLine") (10 7779.0679411765
8102.6300904977 0.0) (11 8034.8180656109 8102.6300904977 0.0))
((0 . "LINE") (100 . "AcDbEntity") (8 . "SOLAR") (62 . 7) (370 . 13) (100 . "AcDbLine") (10 8034.8180656109
8102.6300904977 0.0) (11 8311.3046719457 8102.6300904977 0.0))
((0 . "LINE") (100 . "AcDbEntity") (8 . "SOLAR") (62 . 7) (370 . 13) (100 . "AcDbLine") (10 8311.3046719457
8102.6300904977 0.0) (11 8567.0547963801 8102.6300904977 0.0))
((0 . "LINE") (100 . "AcDbEntity") (8 . "SOLAR") (62 . 7) (370 . 13) (100 . "AcDbLine") (10 7802.3128506787
8063.9423076923 0.0) (11 8058.4605995475 8063.9423076923 0.0))
((0 . "LINE") (100 . "AcDbEntity") (8 . "SOLAR") (62 . 7) (370 . 13) (100 . "AcDbLine") (10 8058.4605995475
8063.9423076923 0.0) (11 8335.3770701357 8063.9423076923 0.0))
((0 . "LINE") (100 . "AcDbEntity") (8 . "SOLAR") (62 . 7) (370 . 13) (100 . "AcDbLine") (10 8335.3770701357
8063.9423076923 0.0) (11 8591.5248190045 8063.9423076923 0.0))
((0 . "LINE") (100 . "AcDbEntity") (8 . "SOLAR") (62 . 7) (370 . 13) (100 . "AcDbLine") (10 7821.6836085973
8031.7024886878 0.0) (11 8078.1627036199 8031.7024886878 0.0))
((0 . "LINE") (100 . "AcDbEntity") (8 . "SOLAR") (62 . 7) (370 . 13) (100 . "AcDbLine") (10 8078.1627036199
8031.7024886878 0.0) (11 8355.4374095023 8031.7024886878 0.0))
((0 . "LINE") (100 . "AcDbEntity") (8 . "SOLAR") (62 . 7) (370 . 13) (100 . "AcDbLine") (10 8355.4374095023
8031.7024886878 0.0) (11 8611.9165045249 8031.7024886878 0.0))
((0 . "LINE") (100 . "AcDbEntity") (8 . "SOLAR") (62 . 7) (370 . 13) (100 . "AcDbLine") (10 7842.0229072398
7997.850678733 0.0) (11 8098.8499208145 7997.850678733 0.0))
((0 . "LINE") (100 . "AcDbEntity") (8 . "SOLAR") (62 . 7) (370 . 13) (100 . "AcDbLine") (10 8098.8499208145
7997.850678733 0.0) (11 8376.5007579186 7997.850678733 0.0))
((0 . "LINE") (100 . "AcDbEntity") (8 . "SOLAR") (62 . 7) (370 . 13) (100 . "AcDbLine") (10 8376.5007579186
7997.850678733 0.0) (11 8633.3277714932 7997.850678733 0.0))
((0 . "LINE") (100 . "AcDbEntity") (8 . "SOLAR") (62 . 7) (370 . 13) (100 . "AcDbLine") (10 7868.1734276018
7954.3269230769 0.0) (11 8125.4477714932 7954.3269230769 0.0))
((0 . "LINE") (100 . "AcDbEntity") (8 . "SOLAR") (62 . 7) (370 . 13) (100 . "AcDbLine") (10 8125.4477714932
7954.3269230769 0.0) (11 8403.5822058824 7954.3269230769 0.0))
((0 . "LINE") (100 . "AcDbEntity") (8 . "SOLAR") (62 . 7) (370 . 13) (100 . "AcDbLine") (10 8403.5822058824
7954.3269230769 0.0) (11 8660.8565497738 7954.3269230769 0.0))
((0 . "LINE") (100 . "AcDbEntity") (8 . "SOLAR") (62 . 7) (370 . 13) (100 . "AcDbLine") (10 8563.3484162896
8212.6696832579 0.0) (11 9287.3303167421 8212.6696832579 0.0))
((0 . "LINE") (100 . "AcDbEntity") (8 . "SOLAR") (62 . 7) (370 . 13) (100 . "AcDbLine") (10 9287.3303167421
8212.6696832579 0.0) (11 9389.1402714932 7873.3031674208 0.0))
((0 . "LINE") (100 . "AcDbEntity") (8 . "SOLAR") (62 . 7) (370 . 13) (100 . "AcDbLine") (10 9389.1402714932
7873.3031674208 0.0) (11 8778.2805429864 7873.3031674208 0.0))
((0 . "LINE") (100 . "AcDbEntity") (8 . "SOLAR") (62 . 7) (370 . 13) (100 . "AcDbLine") (10 8778.2805429864
7873.3031674208 0.0) (11 8563.3484162896 8212.6696832579 0.0))
((0 . "LINE") (100 . "AcDbEntity") (8 . "SOLAR") (62 . 7) (370 . 13) (100 . "AcDbLine") (10 8602.6583710407
8178.7330316742 0.0) (11 8822.3981900452 8178.7330316742 0.0))
((0 . "LINE") (100 . "AcDbEntity") (8 . "SOLAR") (62 . 7) (370 . 13) (100 . "AcDbLine") (10 8822.3981900452
8178.7330316742 0.0) (11 9059.9547511312 8178.7330316742 0.0))
((0 . "LINE") (100 . "AcDbEntity") (8 . "SOLAR") (62 . 7) (370 . 13) (100 . "AcDbLine") (10 9059.9547511312
8178.7330316742 0.0) (11 9279.6945701357 8178.7330316742 0.0))
((0 . "LINE") (100 . "AcDbEntity") (8 . "SOLAR") (62 . 7) (370 . 13) (100 . "AcDbLine") (10 9279.6945701357
8178.7330316742 0.0) (11 9283.7754524887 8165.4977375566 0.0))
((0 . "LINE") (100 . "AcDbEntity") (8 . "SOLAR") (62 . 7) (370 . 13) (100 . "AcDbLine") (10 9283.7754524887
8165.4977375566 0.0) (11 9301.1715271493 8109.0780542986 0.0))
((0 . "LINE") (100 . "AcDbEntity") (8 . "SOLAR") (62 . 7) (370 . 13) (100 . "AcDbLine") (10 9301.1715271493
8109.0780542986 0.0) (11 9314.5913461538 8065.5542986425 0.0))
((0 . "LINE") (100 . "AcDbEntity") (8 . "SOLAR") (62 . 7) (370 . 13) (100 . "AcDbLine") (10 9314.5913461538
8065.5542986425 0.0) (11 9325.0289932127 8031.7024886878 0.0))
((0 . "LINE") (100 . "AcDbEntity") (8 . "SOLAR") (62 . 7) (370 . 13) (100 . "AcDbLine") (10 9325.0289932127
8031.7024886878 0.0) (11 9335.4666289593 7997.850678733 0.0))
((0 . "LINE") (100 . "AcDbEntity") (8 . "SOLAR") (62 . 7) (370 . 13) (100 . "AcDbLine") (10 9335.4666289593
7997.850678733 0.0) (11 9348.886459276 7954.3269230769 0.0))
((0 . "LINE") (100 . "AcDbEntity") (8 . "SOLAR") (62 . 7) (370 . 13) (100 . "AcDbLine") (10 9348.886459276
7954.3269230769 0.0) (11 9360.3181561086 7917.2511312217 0.0))
((0 . "LINE") (100 . "AcDbEntity") (8 . "SOLAR") (62 . 7) (370 . 13) (100 . "AcDbLine") (10 9360.3181561086
7917.2511312217 0.0) (11 9363.4049773756 7907.2398190045 0.0))
((0 . "LINE") (100 . "AcDbEntity") (8 . "SOLAR") (62 . 7) (370 . 13) (100 . "AcDbLine") (10 9363.4049773756
7907.2398190045 0.0) (11 9171.5686312217 7907.2398190045 0.0))
((0 . "LINE") (100 . "AcDbEntity") (8 . "SOLAR") (62 . 7) (370 . 13) (100 . "AcDbLine") (10 9171.5686312217
7907.2398190045 0.0) (11 8964.1779751131 7907.2398190045 0.0))
((0 . "LINE") (100 . "AcDbEntity") (8 . "SOLAR") (62 . 7) (370 . 13) (100 . "AcDbLine") (10 8964.1779751131
7907.2398190045 0.0) (11 8772.3416289593 7907.2398190045 0.0))
((0 . "LINE") (100 . "AcDbEntity") (8 . "SOLAR") (62 . 7) (370 . 13) (100 . "AcDbLine") (10 8772.3416289593
7907.2398190045 0.0) (11 8766.0845588235 7917.2511312217 0.0))
((0 . "LINE") (100 . "AcDbEntity") (8 . "SOLAR") (62 . 7) (370 . 13) (100 . "AcDbLine") (10 8766.0845588235
7917.2511312217 0.0) (11 8742.9121832579 7954.3269230769 0.0))
((0 . "LINE") (100 . "AcDbEntity") (8 . "SOLAR") (62 . 7) (370 . 13) (100 . "AcDbLine") (10 8742.9121832579
7954.3269230769 0.0) (11 8715.709841629 7997.850678733 0.0))
((0 . "LINE") (100 . "AcDbEntity") (8 . "SOLAR") (62 . 7) (370 . 13) (100 . "AcDbLine") (10 8715.709841629
7997.850678733 0.0) (11 8694.5524547511 8031.7024886878 0.0))
((0 . "LINE") (100 . "AcDbEntity") (8 . "SOLAR") (62 . 7) (370 . 13) (100 . "AcDbLine") (10 8694.5524547511
8031.7024886878 0.0) (11 8673.3950791855 8065.5542986425 0.0))
((0 . "LINE") (100 . "AcDbEntity") (8 . "SOLAR") (62 . 7) (370 . 13) (100 . "AcDbLine") (10 8673.3950791855
8065.5542986425 0.0) (11 8646.1927375566 8109.0780542986 0.0))
((0 . "LINE") (100 . "AcDbEntity") (8 . "SOLAR") (62 . 7) (370 . 13) (100 . "AcDbLine") (10 8646.1927375566
8109.0780542986 0.0) (11 8610.9304298643 8165.4977375566 0.0))
((0 . "LINE") (100 . "AcDbEntity") (8 . "SOLAR") (62 . 7) (370 . 13) (100 . "AcDbLine") (10 8610.9304298643
8165.4977375566 0.0) (11 8602.6583710407 8178.7330316742 0.0))
((0 . "LINE") (100 . "AcDbEntity") (8 . "SOLAR") (62 . 7) (370 . 13) (100 . "AcDbLine") (10 8822.3981900452
8178.7330316742 0.0) (11 8829.3099547511 8165.4977375566 0.0))
((0 . "LINE") (100 . "AcDbEntity") (8 . "SOLAR") (62 . 7) (370 . 13) (100 . "AcDbLine") (10 8829.3099547511
8165.4977375566 0.0) (11 8858.7735633484 8109.0780542986 0.0))
((0 . "LINE") (100 . "AcDbEntity") (8 . "SOLAR") (62 . 7) (370 . 13) (100 . "AcDbLine") (10 8858.7735633484
8109.0780542986 0.0) (11 8881.5026357466 8065.5542986425 0.0))
((0 . "LINE") (100 . "AcDbEntity") (8 . "SOLAR") (62 . 7) (370 . 13) (100 . "AcDbLine") (10 8881.5026357466
8065.5542986425 0.0) (11 8899.1808031674 8031.7024886878 0.0))
((0 . "LINE") (100 . "AcDbEntity") (8 . "SOLAR") (62 . 7) (370 . 13) (100 . "AcDbLine") (10 8899.1808031674
8031.7024886878 0.0) (11 8916.8589705882 7997.850678733 0.0))
((0 . "LINE") (100 . "AcDbEntity") (8 . "SOLAR") (62 . 7) (370 . 13) (100 . "AcDbLine") (10 8916.8589705882
7997.850678733 0.0) (11 8939.5880429864 7954.3269230769 0.0))
((0 . "LINE") (100 . "AcDbEntity") (8 . "SOLAR") (62 . 7) (370 . 13) (100 . "AcDbLine") (10 8939.5880429864
7954.3269230769 0.0) (11 8958.9498529412 7917.2511312217 0.0))
((0 . "LINE") (100 . "AcDbEntity") (8 . "SOLAR") (62 . 7) (370 . 13) (100 . "AcDbLine") (10 8958.9498529412
7917.2511312217 0.0) (11 8964.1779751131 7907.2398190045 0.0))
((0 . "LINE") (100 . "AcDbEntity") (8 . "SOLAR") (62 . 7) (370 . 13) (100 . "AcDbLine") (10 9059.9547511312
8178.7330316742 0.0) (11 9065.3959276018 8165.4977375566 0.0))
((0 . "LINE") (100 . "AcDbEntity") (8 . "SOLAR") (62 . 7) (370 . 13) (100 . "AcDbLine") (10 9065.3959276018
8165.4977375566 0.0) (11 9088.5906900453 8109.0780542986 0.0))
((0 . "LINE") (100 . "AcDbEntity") (8 . "SOLAR") (62 . 7) (370 . 13) (100 . "AcDbLine") (10 9088.5906900453
8109.0780542986 0.0) (11 9106.4837895928 8065.5542986425 0.0))
((0 . "LINE") (100 . "AcDbEntity") (8 . "SOLAR") (62 . 7) (370 . 13) (100 . "AcDbLine") (10 9106.4837895928
8065.5542986425 0.0) (11 9120.4006447964 8031.7024886878 0.0))
((0 . "LINE") (100 . "AcDbEntity") (8 . "SOLAR") (62 . 7) (370 . 13) (100 . "AcDbLine") (10 9120.4006447964
8031.7024886878 0.0) (11 9134.3175 7997.850678733 0.0))
((0 . "LINE") (100 . "AcDbEntity") (8 . "SOLAR") (62 . 7) (370 . 13) (100 . "AcDbLine") (10 9134.3175 7997.850678733
0.0) (11 9152.2105995475 7954.3269230769 0.0))
((0 . "LINE") (100 . "AcDbEntity") (8 . "SOLAR") (62 . 7) (370 . 13) (100 . "AcDbLine") (10 9152.2105995475
7954.3269230769 0.0) (11 9167.452861991 7917.2511312217 0.0))
((0 . "LINE") (100 . "AcDbEntity") (8 . "SOLAR") (62 . 7) (370 . 13) (100 . "AcDbLine") (10 9167.452861991
7917.2511312217 0.0) (11 9171.5686312217 7907.2398190045 0.0))
((0 . "LINE") (100 . "AcDbEntity") (8 . "SOLAR") (62 . 7) (370 . 13) (100 . "AcDbLine") (10 8610.9304298643
8165.4977375566 0.0) (11 8829.3099547511 8165.4977375566 0.0))
((0 . "LINE") (100 . "AcDbEntity") (8 . "SOLAR") (62 . 7) (370 . 13) (100 . "AcDbLine") (10 8829.3099547511
8165.4977375566 0.0) (11 9065.3959276018 8165.4977375566 0.0))
((0 . "LINE") (100 . "AcDbEntity") (8 . "SOLAR") (62 . 7) (370 . 13) (100 . "AcDbLine") (10 9065.3959276018
8165.4977375566 0.0) (11 9283.7754524887 8165.4977375566 0.0))
((0 . "LINE") (100 . "AcDbEntity") (8 . "SOLAR") (62 . 7) (370 . 13) (100 . "AcDbLine") (10 8646.1927375566
8109.0780542986 0.0) (11 8858.7735633484 8109.0780542986 0.0))
((0 . "LINE") (100 . "AcDbEntity") (8 . "SOLAR") (62 . 7) (370 . 13) (100 . "AcDbLine") (10 8858.7735633484
8109.0780542986 0.0) (11 9088.5906900453 8109.0780542986 0.0))
((0 . "LINE") (100 . "AcDbEntity") (8 . "SOLAR") (62 . 7) (370 . 13) (100 . "AcDbLine") (10 9088.5906900453
8109.0780542986 0.0) (11 9301.1715271493 8109.0780542986 0.0))
((0 . "LINE") (100 . "AcDbEntity") (8 . "SOLAR") (62 . 7) (370 . 13) (100 . "AcDbLine") (10 8673.3950791855
8065.5542986425 0.0) (11 8881.5026357466 8065.5542986425 0.0))
((0 . "LINE") (100 . "AcDbEntity") (8 . "SOLAR") (62 . 7) (370 . 13) (100 . "AcDbLine") (10 8881.5026357466
8065.5542986425 0.0) (11 9106.4837895928 8065.5542986425 0.0))
((0 . "LINE") (100 . "AcDbEntity") (8 . "SOLAR") (62 . 7) (370 . 13) (100 . "AcDbLine") (10 9106.4837895928
8065.5542986425 0.0) (11 9314.5913461538 8065.5542986425 0.0))
((0 . "LINE") (100 . "AcDbEntity") (8 . "SOLAR") (62 . 7) (370 . 13) (100 . "AcDbLine") (10 8694.5524547511
8031.7024886878 0.0) (11 8899.1808031674 8031.7024886878 0.0))
((0 . "LINE") (100 . "AcDbEntity") (8 . "SOLAR") (62 . 7) (370 . 13) (100 . "AcDbLine") (10 8899.1808031674
8031.7024886878 0.0) (11 9120.4006447964 8031.7024886878 0.0))
((0 . "LINE") (100 . "AcDbEntity") (8 . "SOLAR") (62 . 7) (370 . 13) (100 . "AcDbLine") (10 9120.4006447964
8031.7024886878 0.0) (11 9325.0289932127 8031.7024886878 0.0))
((0 . "LINE") (100 . "AcDbEntity") (8 . "SOLAR") (62 . 7) (370 . 13) (100 . "AcDbLine") (10 8715.709841629
7997.850678733 0.0) (11 8916.8589705882 7997.850678733 0.0))
((0 . "LINE") (100 . "AcDbEntity") (8 . "SOLAR") (62 . 7) (370 . 13) (100 . "AcDbLine") (10 8916.8589705882
7997.850678733 0.0) (11 9134.3175 7997.850678733 0.0))
((0 . "LINE") (100 . "AcDbEntity") (8 . "SOLAR") (62 . 7) (370 . 13) (100 . "AcDbLine") (10 9134.3175 7997.850678733
0.0) (11 9335.4666289593 7997.850678733 0.0))
((0 . "LINE") (100 . "AcDbEntity") (8 . "SOLAR") (62 . 7) (370 . 13) (100 . "AcDbLine") (10 8742.9121832579
7954.3269230769 0.0) (11 8939.5880429864 7954.3269230769 0.0))
((0 . "LINE") (100 . "AcDbEntity") (8 . "SOLAR") (62 . 7) (370 . 13) (100 . "AcDbLine") (10 8939.5880429864
7954.3269230769 0.0) (11 9152.2105995475 7954.3269230769 0.0))
((0 . "LINE") (100 . "AcDbEntity") (8 . "SOLAR") (62 . 7) (370 . 13) (100 . "AcDbLine") (10 9152.2105995475
7954.3269230769 0.0) (11 9348.886459276 7954.3269230769 0.0))
((0 . "LINE") (100 . "AcDbEntity") (8 . "SOLAR") (62 . 7) (370 . 13) (100 . "AcDbLine") (10 8766.0845588235
7917.2511312217 0.0) (11 8958.9498529412 7917.2511312217 0.0))
((0 . "LINE") (100 . "AcDbEntity") (8 . "SOLAR") (62 . 7) (370 . 13) (100 . "AcDbLine") (10 8958.9498529412
7917.2511312217 0.0) (11 9167.452861991 7917.2511312217 0.0))
((0 . "LINE") (100 . "AcDbEntity") (8 . "SOLAR") (62 . 7) (370 . 13) (100 . "AcDbLine") (10 9167.452861991
7917.2511312217 0.0) (11 9360.3181561086 7917.2511312217 0.0))
((0 . "LINE") (100 . "AcDbEntity") (8 . "SOLAR") (62 . 7) (370 . 13) (100 . "AcDbLine") (10 9332.5791855204
8212.6696832579 0.0) (11 9966.0633484163 8212.6696832579 0.0))
((0 . "LINE") (100 . "AcDbEntity") (8 . "SOLAR") (62 . 7) (370 . 13) (100 . "AcDbLine") (10 9966.0633484163
8212.6696832579 0.0) (11 9977.3755656109 7873.3031674208 0.0))
((0 . "LINE") (100 . "AcDbEntity") (8 . "SOLAR") (62 . 7) (370 . 13) (100 . "AcDbLine") (10 9977.3755656109
7873.3031674208 0.0) (11 9434.3891402715 7873.3031674208 0.0))
((0 . "LINE") (100 . "AcDbEntity") (8 . "SOLAR") (62 . 7) (370 . 13) (100 . "AcDbLine") (10 9434.3891402715
7873.3031674208 0.0) (11 9332.5791855204 8212.6696832579 0.0))
((0 . "LINE") (100 . "AcDbEntity") (8 . "SOLAR") (62 . 7) (370 . 13) (100 . "AcDbLine") (10 9358.371040724
8178.7330316742 0.0) (11 9550.9049773756 8178.7330316742 0.0))
((0 . "LINE") (100 . "AcDbEntity") (8 . "SOLAR") (62 . 7) (370 . 13) (100 . "AcDbLine") (10 9550.9049773756
8178.7330316742 0.0) (11 9759.0497737557 8178.7330316742 0.0))
((0 . "LINE") (100 . "AcDbEntity") (8 . "SOLAR") (62 . 7) (370 . 13) (100 . "AcDbLine") (10 9759.0497737557
8178.7330316742 0.0) (11 9951.5837104072 8178.7330316742 0.0))
((0 . "LINE") (100 . "AcDbEntity") (8 . "SOLAR") (62 . 7) (370 . 13) (100 . "AcDbLine") (10 9951.5837104072
8178.7330316742 0.0) (11 9952.1131221719 8165.4977375566 0.0))
((0 . "LINE") (100 . "AcDbEntity") (8 . "SOLAR") (62 . 7) (370 . 13) (100 . "AcDbLine") (10 9952.1131221719
8165.4977375566 0.0) (11 9954.3699095023 8109.0780542986 0.0))
((0 . "LINE") (100 . "AcDbEntity") (8 . "SOLAR") (62 . 7) (370 . 13) (100 . "AcDbLine") (10 9954.3699095023
8109.0780542986 0.0) (11 9956.1753393665 8063.9423076923 0.0))
((0 . "LINE") (100 . "AcDbEntity") (8 . "SOLAR") (62 . 7) (370 . 13) (100 . "AcDbLine") (10 9956.1753393665
8063.9423076923 0.0) (11 9957.4649321267 8031.7024886878 0.0))
((0 . "LINE") (100 . "AcDbEntity") (8 . "SOLAR") (62 . 7) (370 . 13) (100 . "AcDbLine") (10 9957.4649321267
8031.7024886878 0.0) (11 9958.8190045249 7997.850678733 0.0))
((0 . "LINE") (100 . "AcDbEntity") (8 . "SOLAR") (62 . 7) (370 . 13) (100 . "AcDbLine") (10 9958.8190045249
7997.850678733 0.0) (11 9960.5599547511 7954.3269230769 0.0))
((0 . "LINE") (100 . "AcDbEntity") (8 . "SOLAR") (62 . 7) (370 . 13) (100 . "AcDbLine") (10 9960.5599547511
7954.3269230769 0.0) (11 9962.0429864253 7917.2511312217 0.0))
((0 . "LINE") (100 . "AcDbEntity") (8 . "SOLAR") (62 . 7) (370 . 13) (100 . "AcDbLine") (10 9962.0429864253
7917.2511312217 0.0) (11 9962.443438914 7907.2398190045 0.0))
((0 . "LINE") (100 . "AcDbEntity") (8 . "SOLAR") (62 . 7) (370 . 13) (100 . "AcDbLine") (10 9962.443438914
7907.2398190045 0.0) (11 9792.2322737557 7907.2398190045 0.0))
((0 . "LINE") (100 . "AcDbEntity") (8 . "SOLAR") (62 . 7) (370 . 13) (100 . "AcDbLine") (10 9792.2322737557
7907.2398190045 0.0) (11 9608.2202149321 7907.2398190045 0.0))
((0 . "LINE") (100 . "AcDbEntity") (8 . "SOLAR") (62 . 7) (370 . 13) (100 . "AcDbLine") (10 9608.2202149321
7907.2398190045 0.0) (11 9438.0090497738 7907.2398190045 0.0))
((0 . "LINE") (100 . "AcDbEntity") (8 . "SOLAR") (62 . 7) (370 . 13) (100 . "AcDbLine") (10 9438.0090497738
7907.2398190045 0.0) (11 9435.07239819 7917.2511312217 0.0))
((0 . "LINE") (100 . "AcDbEntity") (8 . "SOLAR") (62 . 7) (370 . 13) (100 . "AcDbLine") (10 9435.07239819
7917.2511312217 0.0) (11 9424.1968325792 7954.3269230769 0.0))
((0 . "LINE") (100 . "AcDbEntity") (8 . "SOLAR") (62 . 7) (370 . 13) (100 . "AcDbLine") (10 9424.1968325792
7954.3269230769 0.0) (11 9411.4298642534 7997.850678733 0.0))
((0 . "LINE") (100 . "AcDbEntity") (8 . "SOLAR") (62 . 7) (370 . 13) (100 . "AcDbLine") (10 9411.4298642534
7997.850678733 0.0) (11 9401.5 8031.7024886878 0.0))
((0 . "LINE") (100 . "AcDbEntity") (8 . "SOLAR") (62 . 7) (370 . 13) (100 . "AcDbLine") (10 9401.5 8031.7024886878 0.0)
(11 9392.0429864253 8063.9423076923 0.0))
((0 . "LINE") (100 . "AcDbEntity") (8 . "SOLAR") (62 . 7) (370 . 13) (100 . "AcDbLine") (10 9392.0429864253
8063.9423076923 0.0) (11 9378.8031674208 8109.0780542986 0.0))
((0 . "LINE") (100 . "AcDbEntity") (8 . "SOLAR") (62 . 7) (370 . 13) (100 . "AcDbLine") (10 9378.8031674208
8109.0780542986 0.0) (11 9362.2533936652 8165.4977375566 0.0))
((0 . "LINE") (100 . "AcDbEntity") (8 . "SOLAR") (62 . 7) (370 . 13) (100 . "AcDbLine") (10 9362.2533936652
8165.4977375566 0.0) (11 9358.371040724 8178.7330316742 0.0))
((0 . "LINE") (100 . "AcDbEntity") (8 . "SOLAR") (62 . 7) (370 . 13) (100 . "AcDbLine") (10 9550.9049773756
8178.7330316742 0.0) (11 9553.6990950226 8165.4977375566 0.0))
((0 . "LINE") (100 . "AcDbEntity") (8 . "SOLAR") (62 . 7) (370 . 13) (100 . "AcDbLine") (10 9553.6990950226
8165.4977375566 0.0) (11 9565.6099208145 8109.0780542986 0.0))
((0 . "LINE") (100 . "AcDbEntity") (8 . "SOLAR") (62 . 7) (370 . 13) (100 . "AcDbLine") (10 9565.6099208145
8109.0780542986 0.0) (11 9575.1385746606 8063.9423076923 0.0))
((0 . "LINE") (100 . "AcDbEntity") (8 . "SOLAR") (62 . 7) (370 . 13) (100 . "AcDbLine") (10 9575.1385746606
8063.9423076923 0.0) (11 9581.9447624434 8031.7024886878 0.0))
((0 . "LINE") (100 . "AcDbEntity") (8 . "SOLAR") (62 . 7) (370 . 13) (100 . "AcDbLine") (10 9581.9447624434
8031.7024886878 0.0) (11 9589.0912556561 7997.850678733 0.0))
((0 . "LINE") (100 . "AcDbEntity") (8 . "SOLAR") (62 . 7) (370 . 13) (100 . "AcDbLine") (10 9589.0912556561
7997.850678733 0.0) (11 9598.2796040724 7954.3269230769 0.0))
((0 . "LINE") (100 . "AcDbEntity") (8 . "SOLAR") (62 . 7) (370 . 13) (100 . "AcDbLine") (10 9598.2796040724
7954.3269230769 0.0) (11 9606.1067081448 7917.2511312217 0.0))
((0 . "LINE") (100 . "AcDbEntity") (8 . "SOLAR") (62 . 7) (370 . 13) (100 . "AcDbLine") (10 9606.1067081448
7917.2511312217 0.0) (11 9608.2202149321 7907.2398190045 0.0))
((0 . "LINE") (100 . "AcDbEntity") (8 . "SOLAR") (62 . 7) (370 . 13) (100 . "AcDbLine") (10 9759.0497737557
8178.7330316742 0.0) (11 9760.6674208145 8165.4977375566 0.0))
((0 . "LINE") (100 . "AcDbEntity") (8 . "SOLAR") (62 . 7) (370 . 13) (100 . "AcDbLine") (10 9760.6674208145
8165.4977375566 0.0) (11 9767.5631561086 8109.0780542986 0.0))
((0 . "LINE") (100 . "AcDbEntity") (8 . "SOLAR") (62 . 7) (370 . 13) (100 . "AcDbLine") (10 9767.5631561086
8109.0780542986 0.0) (11 9773.0797511312 8063.9423076923 0.0))
((0 . "LINE") (100 . "AcDbEntity") (8 . "SOLAR") (62 . 7) (370 . 13) (100 . "AcDbLine") (10 9773.0797511312
8063.9423076923 0.0) (11 9777.0201696833 8031.7024886878 0.0))
((0 . "LINE") (100 . "AcDbEntity") (8 . "SOLAR") (62 . 7) (370 . 13) (100 . "AcDbLine") (10 9777.0201696833
8031.7024886878 0.0) (11 9781.1576131222 7997.850678733 0.0))
((0 . "LINE") (100 . "AcDbEntity") (8 . "SOLAR") (62 . 7) (370 . 13) (100 . "AcDbLine") (10 9781.1576131222
7997.850678733 0.0) (11 9786.4771832579 7954.3269230769 0.0))
((0 . "LINE") (100 . "AcDbEntity") (8 . "SOLAR") (62 . 7) (370 . 13) (100 . "AcDbLine") (10 9786.4771832579
7954.3269230769 0.0) (11 9791.0086764706 7917.2511312217 0.0))
((0 . "LINE") (100 . "AcDbEntity") (8 . "SOLAR") (62 . 7) (370 . 13) (100 . "AcDbLine") (10 9791.0086764706
7917.2511312217 0.0) (11 9792.2322737557 7907.2398190045 0.0))
((0 . "LINE") (100 . "AcDbEntity") (8 . "SOLAR") (62 . 7) (370 . 13) (100 . "AcDbLine") (10 9362.2533936652
8165.4977375566 0.0) (11 9553.6990950226 8165.4977375566 0.0))
((0 . "LINE") (100 . "AcDbEntity") (8 . "SOLAR") (62 . 7) (370 . 13) (100 . "AcDbLine") (10 9553.6990950226
8165.4977375566 0.0) (11 9760.6674208145 8165.4977375566 0.0))
((0 . "LINE") (100 . "AcDbEntity") (8 . "SOLAR") (62 . 7) (370 . 13) (100 . "AcDbLine") (10 9760.6674208145
8165.4977375566 0.0) (11 9952.1131221719 8165.4977375566 0.0))
((0 . "LINE") (100 . "AcDbEntity") (8 . "SOLAR") (62 . 7) (370 . 13) (100 . "AcDbLine") (10 9378.8031674208
8109.0780542986 0.0) (11 9565.6099208145 8109.0780542986 0.0))
((0 . "LINE") (100 . "AcDbEntity") (8 . "SOLAR") (62 . 7) (370 . 13) (100 . "AcDbLine") (10 9565.6099208145
8109.0780542986 0.0) (11 9767.5631561086 8109.0780542986 0.0))
((0 . "LINE") (100 . "AcDbEntity") (8 . "SOLAR") (62 . 7) (370 . 13) (100 . "AcDbLine") (10 9767.5631561086
8109.0780542986 0.0) (11 9954.3699095023 8109.0780542986 0.0))
((0 . "LINE") (100 . "AcDbEntity") (8 . "SOLAR") (62 . 7) (370 . 13) (100 . "AcDbLine") (10 9392.0429864253
8063.9423076923 0.0) (11 9575.1385746606 8063.9423076923 0.0))
((0 . "LINE") (100 . "AcDbEntity") (8 . "SOLAR") (62 . 7) (370 . 13) (100 . "AcDbLine") (10 9575.1385746606
8063.9423076923 0.0) (11 9773.0797511312 8063.9423076923 0.0))
((0 . "LINE") (100 . "AcDbEntity") (8 . "SOLAR") (62 . 7) (370 . 13) (100 . "AcDbLine") (10 9773.0797511312
8063.9423076923 0.0) (11 9956.1753393665 8063.9423076923 0.0))
((0 . "LINE") (100 . "AcDbEntity") (8 . "SOLAR") (62 . 7) (370 . 13) (100 . "AcDbLine") (10 9401.5 8031.7024886878 0.0)
(11 9581.9447624434 8031.7024886878 0.0))
((0 . "LINE") (100 . "AcDbEntity") (8 . "SOLAR") (62 . 7) (370 . 13) (100 . "AcDbLine") (10 9581.9447624434
8031.7024886878 0.0) (11 9777.0201696833 8031.7024886878 0.0))
((0 . "LINE") (100 . "AcDbEntity") (8 . "SOLAR") (62 . 7) (370 . 13) (100 . "AcDbLine") (10 9777.0201696833
8031.7024886878 0.0) (11 9957.4649321267 8031.7024886878 0.0))
((0 . "LINE") (100 . "AcDbEntity") (8 . "SOLAR") (62 . 7) (370 . 13) (100 . "AcDbLine") (10 9411.4298642534
7997.850678733 0.0) (11 9589.0912556561 7997.850678733 0.0))
((0 . "LINE") (100 . "AcDbEntity") (8 . "SOLAR") (62 . 7) (370 . 13) (100 . "AcDbLine") (10 9589.0912556561
7997.850678733 0.0) (11 9781.1576131222 7997.850678733 0.0))
((0 . "LINE") (100 . "AcDbEntity") (8 . "SOLAR") (62 . 7) (370 . 13) (100 . "AcDbLine") (10 9781.1576131222
7997.850678733 0.0) (11 9958.8190045249 7997.850678733 0.0))
((0 . "LINE") (100 . "AcDbEntity") (8 . "SOLAR") (62 . 7) (370 . 13) (100 . "AcDbLine") (10 9424.1968325792
7954.3269230769 0.0) (11 9598.2796040724 7954.3269230769 0.0))
((0 . "LINE") (100 . "AcDbEntity") (8 . "SOLAR") (62 . 7) (370 . 13) (100 . "AcDbLine") (10 9598.2796040724
7954.3269230769 0.0) (11 9786.4771832579 7954.3269230769 0.0))
((0 . "LINE") (100 . "AcDbEntity") (8 . "SOLAR") (62 . 7) (370 . 13) (100 . "AcDbLine") (10 9786.4771832579
7954.3269230769 0.0) (11 9960.5599547511 7954.3269230769 0.0))
((0 . "LINE") (100 . "AcDbEntity") (8 . "SOLAR") (62 . 7) (370 . 13) (100 . "AcDbLine") (10 9435.07239819
7917.2511312217 0.0) (11 9606.1067081448 7917.2511312217 0.0))
((0 . "LINE") (100 . "AcDbEntity") (8 . "SOLAR") (62 . 7) (370 . 13) (100 . "AcDbLine") (10 9606.1067081448
7917.2511312217 0.0) (11 9791.0086764706 7917.2511312217 0.0))
((0 . "LINE") (100 . "AcDbEntity") (8 . "SOLAR") (62 . 7) (370 . 13) (100 . "AcDbLine") (10 9791.0086764706
7917.2511312217 0.0) (11 9962.0429864253 7917.2511312217 0.0))
((0 . "LINE") (100 . "AcDbEntity") (8 . "SOLAR") (62 . 7) (370 . 13) (100 . "AcDbLine") (10 10022.6244343891
8212.6696832579 0.0) (11 10633.4841628959 8212.6696832579 0.0))
((0 . "LINE") (100 . "AcDbEntity") (8 . "SOLAR") (62 . 7) (370 . 13) (100 . "AcDbLine") (10 10633.4841628959
8212.6696832579 0.0) (11 10576.9230769231 7873.3031674208 0.0))
((0 . "LINE") (100 . "AcDbEntity") (8 . "SOLAR") (62 . 7) (370 . 13) (100 . "AcDbLine") (10 10576.9230769231
7873.3031674208 0.0) (11 10011.3122171946 7873.3031674208 0.0))
((0 . "LINE") (100 . "AcDbEntity") (8 . "SOLAR") (62 . 7) (370 . 13) (100 . "AcDbLine") (10 10011.3122171946
7873.3031674208 0.0) (11 10022.6244343891 8212.6696832579 0.0))
((0 . "LINE") (100 . "AcDbEntity") (8 . "SOLAR") (62 . 7) (370 . 13) (100 . "AcDbLine") (10 10036.6515837104
8178.7330316742 0.0) (11 10223.6048303167 8178.7330316742 0.0))
((0 . "LINE") (100 . "AcDbEntity") (8 . "SOLAR") (62 . 7) (370 . 13) (100 . "AcDbLine") (10 10223.6048303167
8178.7330316742 0.0) (11 10425.7164366516 8178.7330316742 0.0))
((0 . "LINE") (100 . "AcDbEntity") (8 . "SOLAR") (62 . 7) (370 . 13) (100 . "AcDbLine") (10 10425.7164366516
8178.7330316742 0.0) (11 10612.6696832579 8178.7330316742 0.0))
((0 . "LINE") (100 . "AcDbEntity") (8 . "SOLAR") (62 . 7) (370 . 13) (100 . "AcDbLine") (10 10612.6696832579
8178.7330316742 0.0) (11 10610.507918552 8165.4977375566 0.0))
((0 . "LINE") (100 . "AcDbEntity") (8 . "SOLAR") (62 . 7) (370 . 13) (100 . "AcDbLine") (10 10610.507918552
8165.4977375566 0.0) (11 10601.2927036199 8109.0780542986 0.0))
((0 . "LINE") (100 . "AcDbEntity") (8 . "SOLAR") (62 . 7) (370 . 13) (100 . "AcDbLine") (10 10601.2927036199
8109.0780542986 0.0) (11 10594.1838235294 8065.5542986425 0.0))
((0 . "LINE") (100 . "AcDbEntity") (8 . "SOLAR") (62 . 7) (370 . 13) (100 . "AcDbLine") (10 10594.1838235294
8065.5542986425 0.0) (11 10588.6546945701 8031.7024886878 0.0))
((0 . "LINE") (100 . "AcDbEntity") (8 . "SOLAR") (62 . 7) (370 . 13) (100 . "AcDbLine") (10 10588.6546945701
8031.7024886878 0.0) (11 10583.1255656109 7997.850678733 0.0))
((0 . "LINE") (100 . "AcDbEntity") (8 . "SOLAR") (62 . 7) (370 . 13) (100 . "AcDbLine") (10 10583.1255656109
7997.850678733 0.0) (11 10576.0166855204 7954.3269230769 0.0))
((0 . "LINE") (100 . "AcDbEntity") (8 . "SOLAR") (62 . 7) (370 . 13) (100 . "AcDbLine") (10 10576.0166855204
7954.3269230769 0.0) (11 10569.9609728507 7917.2511312217 0.0))
((0 . "LINE") (100 . "AcDbEntity") (8 . "SOLAR") (62 . 7) (370 . 13) (100 . "AcDbLine") (10 10569.9609728507
7917.2511312217 0.0) (11 10568.3257918552 7907.2398190045 0.0))
((0 . "LINE") (100 . "AcDbEntity") (8 . "SOLAR") (62 . 7) (370 . 13) (100 . "AcDbLine") (10 10568.3257918552
7907.2398190045 0.0) (11 10392.5339366516 7907.2398190045 0.0))
((0 . "LINE") (100 . "AcDbEntity") (8 . "SOLAR") (62 . 7) (370 . 13) (100 . "AcDbLine") (10 10392.5339366516
7907.2398190045 0.0) (11 10202.4886877828 7907.2398190045 0.0))
((0 . "LINE") (100 . "AcDbEntity") (8 . "SOLAR") (62 . 7) (370 . 13) (100 . "AcDbLine") (10 10202.4886877828
7907.2398190045 0.0) (11 10026.6968325792 7907.2398190045 0.0))
((0 . "LINE") (100 . "AcDbEntity") (8 . "SOLAR") (62 . 7) (370 . 13) (100 . "AcDbLine") (10 10026.6968325792
7907.2398190045 0.0) (11 10027.0639140272 7917.2511312217 0.0))
((0 . "LINE") (100 . "AcDbEntity") (8 . "SOLAR") (62 . 7) (370 . 13) (100 . "AcDbLine") (10 10027.0639140272
7917.2511312217 0.0) (11 10028.4233597285 7954.3269230769 0.0))
((0 . "LINE") (100 . "AcDbEntity") (8 . "SOLAR") (62 . 7) (370 . 13) (100 . "AcDbLine") (10 10028.4233597285
7954.3269230769 0.0) (11 10030.0192307692 7997.850678733 0.0))
((0 . "LINE") (100 . "AcDbEntity") (8 . "SOLAR") (62 . 7) (370 . 13) (100 . "AcDbLine") (10 10030.0192307692
7997.850678733 0.0) (11 10031.2604638009 8031.7024886878 0.0))
((0 . "LINE") (100 . "AcDbEntity") (8 . "SOLAR") (62 . 7) (370 . 13) (100 . "AcDbLine") (10 10031.2604638009
8031.7024886878 0.0) (11 10032.5016968326 8065.5542986425 0.0))
((0 . "LINE") (100 . "AcDbEntity") (8 . "SOLAR") (62 . 7) (370 . 13) (100 . "AcDbLine") (10 10032.5016968326
8065.5542986425 0.0) (11 10034.0975678733 8109.0780542986 0.0))
((0 . "LINE") (100 . "AcDbEntity") (8 . "SOLAR") (62 . 7) (370 . 13) (100 . "AcDbLine") (10 10034.0975678733
8109.0780542986 0.0) (11 10036.1662895928 8165.4977375566 0.0))
((0 . "LINE") (100 . "AcDbEntity") (8 . "SOLAR") (62 . 7) (370 . 13) (100 . "AcDbLine") (10 10036.1662895928
8165.4977375566 0.0) (11 10036.6515837104 8178.7330316742 0.0))
((0 . "LINE") (100 . "AcDbEntity") (8 . "SOLAR") (62 . 7) (370 . 13) (100 . "AcDbLine") (10 10223.6048303167
8178.7330316742 0.0) (11 10222.575418552 8165.4977375566 0.0))
((0 . "LINE") (100 . "AcDbEntity") (8 . "SOLAR") (62 . 7) (370 . 13) (100 . "AcDbLine") (10 10222.575418552
8165.4977375566 0.0) (11 10218.1872171946 8109.0780542986 0.0))
((0 . "LINE") (100 . "AcDbEntity") (8 . "SOLAR") (62 . 7) (370 . 13) (100 . "AcDbLine") (10 10218.1872171946
8109.0780542986 0.0) (11 10214.8020361991 8065.5542986425 0.0))
((0 . "LINE") (100 . "AcDbEntity") (8 . "SOLAR") (62 . 7) (370 . 13) (100 . "AcDbLine") (10 10214.8020361991
8065.5542986425 0.0) (11 10212.1691176471 8031.7024886878 0.0))
((0 . "LINE") (100 . "AcDbEntity") (8 . "SOLAR") (62 . 7) (370 . 13) (100 . "AcDbLine") (10 10212.1691176471
8031.7024886878 0.0) (11 10209.536199095 7997.850678733 0.0))
((0 . "LINE") (100 . "AcDbEntity") (8 . "SOLAR") (62 . 7) (370 . 13) (100 . "AcDbLine") (10 10209.536199095
7997.850678733 0.0) (11 10206.1510180995 7954.3269230769 0.0))
((0 . "LINE") (100 . "AcDbEntity") (8 . "SOLAR") (62 . 7) (370 . 13) (100 . "AcDbLine") (10 10206.1510180995
7954.3269230769 0.0) (11 10203.267341629 7917.2511312217 0.0))
((0 . "LINE") (100 . "AcDbEntity") (8 . "SOLAR") (62 . 7) (370 . 13) (100 . "AcDbLine") (10 10203.267341629
7917.2511312217 0.0) (11 10202.4886877828 7907.2398190045 0.0))
((0 . "LINE") (100 . "AcDbEntity") (8 . "SOLAR") (62 . 7) (370 . 13) (100 . "AcDbLine") (10 10425.7164366516
8178.7330316742 0.0) (11 10424.0987895928 8165.4977375566 0.0))
((0 . "LINE") (100 . "AcDbEntity") (8 . "SOLAR") (62 . 7) (370 . 13) (100 . "AcDbLine") (10 10424.0987895928
8165.4977375566 0.0) (11 10417.2030542986 8109.0780542986 0.0))
((0 . "LINE") (100 . "AcDbEntity") (8 . "SOLAR") (62 . 7) (370 . 13) (100 . "AcDbLine") (10 10417.2030542986
8109.0780542986 0.0) (11 10411.8834841629 8065.5542986425 0.0))
((0 . "LINE") (100 . "AcDbEntity") (8 . "SOLAR") (62 . 7) (370 . 13) (100 . "AcDbLine") (10 10411.8834841629
8065.5542986425 0.0) (11 10407.746040724 8031.7024886878 0.0))
((0 . "LINE") (100 . "AcDbEntity") (8 . "SOLAR") (62 . 7) (370 . 13) (100 . "AcDbLine") (10 10407.746040724
8031.7024886878 0.0) (11 10403.6085972851 7997.850678733 0.0))
((0 . "LINE") (100 . "AcDbEntity") (8 . "SOLAR") (62 . 7) (370 . 13) (100 . "AcDbLine") (10 10403.6085972851
7997.850678733 0.0) (11 10398.2890271493 7954.3269230769 0.0))
((0 . "LINE") (100 . "AcDbEntity") (8 . "SOLAR") (62 . 7) (370 . 13) (100 . "AcDbLine") (10 10398.2890271493
7954.3269230769 0.0) (11 10393.7575452489 7917.2511312217 0.0))
((0 . "LINE") (100 . "AcDbEntity") (8 . "SOLAR") (62 . 7) (370 . 13) (100 . "AcDbLine") (10 10393.7575452489
7917.2511312217 0.0) (11 10392.5339366516 7907.2398190045 0.0))
((0 . "LINE") (100 . "AcDbEntity") (8 . "SOLAR") (62 . 7) (370 . 13) (100 . "AcDbLine") (10 10036.1662895928
8165.4977375566 0.0) (11 10222.575418552 8165.4977375566 0.0))
((0 . "LINE") (100 . "AcDbEntity") (8 . "SOLAR") (62 . 7) (370 . 13) (100 . "AcDbLine") (10 10222.575418552
8165.4977375566 0.0) (11 10424.0987895928 8165.4977375566 0.0))
((0 . "LINE") (100 . "AcDbEntity") (8 . "SOLAR") (62 . 7) (370 . 13) (100 . "AcDbLine") (10 10424.0987895928
8165.4977375566 0.0) (11 10610.507918552 8165.4977375566 0.0))
((0 . "LINE") (100 . "AcDbEntity") (8 . "SOLAR") (62 . 7) (370 . 13) (100 . "AcDbLine") (10 10034.0975678733
8109.0780542986 0.0) (11 10218.1872171946 8109.0780542986 0.0))
((0 . "LINE") (100 . "AcDbEntity") (8 . "SOLAR") (62 . 7) (370 . 13) (100 . "AcDbLine") (10 10218.1872171946
8109.0780542986 0.0) (11 10417.2030542986 8109.0780542986 0.0))
((0 . "LINE") (100 . "AcDbEntity") (8 . "SOLAR") (62 . 7) (370 . 13) (100 . "AcDbLine") (10 10417.2030542986
8109.0780542986 0.0) (11 10601.2927036199 8109.0780542986 0.0))
((0 . "LINE") (100 . "AcDbEntity") (8 . "SOLAR") (62 . 7) (370 . 13) (100 . "AcDbLine") (10 10032.5016968326
8065.5542986425 0.0) (11 10214.8020361991 8065.5542986425 0.0))
((0 . "LINE") (100 . "AcDbEntity") (8 . "SOLAR") (62 . 7) (370 . 13) (100 . "AcDbLine") (10 10214.8020361991
8065.5542986425 0.0) (11 10411.8834841629 8065.5542986425 0.0))
((0 . "LINE") (100 . "AcDbEntity") (8 . "SOLAR") (62 . 7) (370 . 13) (100 . "AcDbLine") (10 10411.8834841629
8065.5542986425 0.0) (11 10594.1838235294 8065.5542986425 0.0))
((0 . "LINE") (100 . "AcDbEntity") (8 . "SOLAR") (62 . 7) (370 . 13) (100 . "AcDbLine") (10 10031.2604638009
8031.7024886878 0.0) (11 10212.1691176471 8031.7024886878 0.0))
((0 . "LINE") (100 . "AcDbEntity") (8 . "SOLAR") (62 . 7) (370 . 13) (100 . "AcDbLine") (10 10212.1691176471
8031.7024886878 0.0) (11 10407.746040724 8031.7024886878 0.0))
((0 . "LINE") (100 . "AcDbEntity") (8 . "SOLAR") (62 . 7) (370 . 13) (100 . "AcDbLine") (10 10407.746040724
8031.7024886878 0.0) (11 10588.6546945701 8031.7024886878 0.0))
((0 . "LINE") (100 . "AcDbEntity") (8 . "SOLAR") (62 . 7) (370 . 13) (100 . "AcDbLine") (10 10030.0192307692
7997.850678733 0.0) (11 10209.536199095 7997.850678733 0.0))
((0 . "LINE") (100 . "AcDbEntity") (8 . "SOLAR") (62 . 7) (370 . 13) (100 . "AcDbLine") (10 10209.536199095
7997.850678733 0.0) (11 10403.6085972851 7997.850678733 0.0))
((0 . "LINE") (100 . "AcDbEntity") (8 . "SOLAR") (62 . 7) (370 . 13) (100 . "AcDbLine") (10 10403.6085972851
7997.850678733 0.0) (11 10583.1255656109 7997.850678733 0.0))
((0 . "LINE") (100 . "AcDbEntity") (8 . "SOLAR") (62 . 7) (370 . 13) (100 . "AcDbLine") (10 10028.4233597285
7954.3269230769 0.0) (11 10206.1510180995 7954.3269230769 0.0))
((0 . "LINE") (100 . "AcDbEntity") (8 . "SOLAR") (62 . 7) (370 . 13) (100 . "AcDbLine") (10 10206.1510180995
7954.3269230769 0.0) (11 10398.2890271493 7954.3269230769 0.0))
((0 . "LINE") (100 . "AcDbEntity") (8 . "SOLAR") (62 . 7) (370 . 13) (100 . "AcDbLine") (10 10398.2890271493
7954.3269230769 0.0) (11 10576.0166855204 7954.3269230769 0.0))
((0 . "LINE") (100 . "AcDbEntity") (8 . "SOLAR") (62 . 7) (370 . 13) (100 . "AcDbLine") (10 10027.0639140272
7917.2511312217 0.0) (11 10203.267341629 7917.2511312217 0.0))
((0 . "LINE") (100 . "AcDbEntity") (8 . "SOLAR") (62 . 7) (370 . 13) (100 . "AcDbLine") (10 10203.267341629
7917.2511312217 0.0) (11 10393.7575452489 7917.2511312217 0.0))
((0 . "LINE") (100 . "AcDbEntity") (8 . "SOLAR") (62 . 7) (370 . 13) (100 . "AcDbLine") (10 10393.7575452489
7917.2511312217 0.0) (11 10569.9609728507 7917.2511312217 0.0))
((0 . "LINE") (100 . "AcDbEntity") (8 . "SOLAR") (62 . 7) (370 . 13) (100 . "AcDbLine") (10 10667.4208144796
8212.6696832579 0.0) (11 11300.9049773756 8212.6696832579 0.0))
((0 . "LINE") (100 . "AcDbEntity") (8 . "SOLAR") (62 . 7) (370 . 13) (100 . "AcDbLine") (10 11300.9049773756
8212.6696832579 0.0) (11 11153.8461538462 7873.3031674208 0.0))
((0 . "LINE") (100 . "AcDbEntity") (8 . "SOLAR") (62 . 7) (370 . 13) (100 . "AcDbLine") (10 11153.8461538462
7873.3031674208 0.0) (11 10622.1719457014 7873.3031674208 0.0))
((0 . "LINE") (100 . "AcDbEntity") (8 . "SOLAR") (62 . 7) (370 . 13) (100 . "AcDbLine") (10 10622.1719457014
7873.3031674208 0.0) (11 10667.4208144796 8212.6696832579 0.0))
((0 . "LINE") (100 . "AcDbEntity") (8 . "SOLAR") (62 . 7) (370 . 13) (100 . "AcDbLine") (10 10678.4785067873
8178.7330316742 0.0) (11 10870.6636538462 8178.7330316742 0.0))
((0 . "LINE") (100 . "AcDbEntity") (8 . "SOLAR") (62 . 7) (370 . 13) (100 . "AcDbLine") (10 10870.6636538462
8178.7330316742 0.0) (11 11078.4313687783 8178.7330316742 0.0))
((0 . "LINE") (100 . "AcDbEntity") (8 . "SOLAR") (62 . 7) (370 . 13) (100 . "AcDbLine") (10 11078.4313687783
8178.7330316742 0.0) (11 11270.6165158371 8178.7330316742 0.0))
((0 . "LINE") (100 . "AcDbEntity") (8 . "SOLAR") (62 . 7) (370 . 13) (100 . "AcDbLine") (10 11270.6165158371
8178.7330316742 0.0) (11 11264.9804864253 8165.4977375566 0.0))
((0 . "LINE") (100 . "AcDbEntity") (8 . "SOLAR") (62 . 7) (370 . 13) (100 . "AcDbLine") (10 11264.9804864253
8165.4977375566 0.0) (11 11240.95510181 8109.0780542986 0.0))
((0 . "LINE") (100 . "AcDbEntity") (8 . "SOLAR") (62 . 7) (370 . 13) (100 . "AcDbLine") (10 11240.95510181
8109.0780542986 0.0) (11 11221.7347963801 8063.9423076923 0.0))
((0 . "LINE") (100 . "AcDbEntity") (8 . "SOLAR") (62 . 7) (370 . 13) (100 . "AcDbLine") (10 11221.7347963801
8063.9423076923 0.0) (11 11208.0060067873 8031.7024886878 0.0))
((0 . "LINE") (100 . "AcDbEntity") (8 . "SOLAR") (62 . 7) (370 . 13) (100 . "AcDbLine") (10 11208.0060067873
8031.7024886878 0.0) (11 11193.590780543 7997.850678733 0.0))
((0 . "LINE") (100 . "AcDbEntity") (8 . "SOLAR") (62 . 7) (370 . 13) (100 . "AcDbLine") (10 11193.590780543
7997.850678733 0.0) (11 11175.0569117647 7954.3269230769 0.0))
((0 . "LINE") (100 . "AcDbEntity") (8 . "SOLAR") (62 . 7) (370 . 13) (100 . "AcDbLine") (10 11175.0569117647
7954.3269230769 0.0) (11 11159.268800905 7917.2511312217 0.0))
((0 . "LINE") (100 . "AcDbEntity") (8 . "SOLAR") (62 . 7) (370 . 13) (100 . "AcDbLine") (10 11159.268800905
7917.2511312217 0.0) (11 11155.0056561086 7907.2398190045 0.0))
((0 . "LINE") (100 . "AcDbEntity") (8 . "SOLAR") (62 . 7) (370 . 13) (100 . "AcDbLine") (10 11155.0056561086
7907.2398190045 0.0) (11 10987.9336312217 7907.2398190045 0.0))
((0 . "LINE") (100 . "AcDbEntity") (8 . "SOLAR") (62 . 7) (370 . 13) (100 . "AcDbLine") (10 10987.9336312217
7907.2398190045 0.0) (11 10807.3152375566 7907.2398190045 0.0))
((0 . "LINE") (100 . "AcDbEntity") (8 . "SOLAR") (62 . 7) (370 . 13) (100 . "AcDbLine") (10 10807.3152375566
7907.2398190045 0.0) (11 10640.2432126697 7907.2398190045 0.0))
((0 . "LINE") (100 . "AcDbEntity") (8 . "SOLAR") (62 . 7) (370 . 13) (100 . "AcDbLine") (10 10640.2432126697
7907.2398190045 0.0) (11 10641.6531334842 7917.2511312217 0.0))
((0 . "LINE") (100 . "AcDbEntity") (8 . "SOLAR") (62 . 7) (370 . 13) (100 . "AcDbLine") (10 10641.6531334842
7917.2511312217 0.0) (11 10646.8746493213 7954.3269230769 0.0))
((0 . "LINE") (100 . "AcDbEntity") (8 . "SOLAR") (62 . 7) (370 . 13) (100 . "AcDbLine") (10 10646.8746493213
7954.3269230769 0.0) (11 10653.0042420814 7997.850678733 0.0))
((0 . "LINE") (100 . "AcDbEntity") (8 . "SOLAR") (62 . 7) (370 . 13) (100 . "AcDbLine") (10 10653.0042420814
7997.850678733 0.0) (11 10657.7717081448 8031.7024886878 0.0))
((0 . "LINE") (100 . "AcDbEntity") (8 . "SOLAR") (62 . 7) (370 . 13) (100 . "AcDbLine") (10 10657.7717081448
8031.7024886878 0.0) (11 10662.3121493213 8063.9423076923 0.0))
((0 . "LINE") (100 . "AcDbEntity") (8 . "SOLAR") (62 . 7) (370 . 13) (100 . "AcDbLine") (10 10662.3121493213
8063.9423076923 0.0) (11 10668.6687669683 8109.0780542986 0.0))
((0 . "LINE") (100 . "AcDbEntity") (8 . "SOLAR") (62 . 7) (370 . 13) (100 . "AcDbLine") (10 10668.6687669683
8109.0780542986 0.0) (11 10676.6145361991 8165.4977375566 0.0))
((0 . "LINE") (100 . "AcDbEntity") (8 . "SOLAR") (62 . 7) (370 . 13) (100 . "AcDbLine") (10 10676.6145361991
8165.4977375566 0.0) (11 10678.4785067873 8178.7330316742 0.0))
((0 . "LINE") (100 . "AcDbEntity") (8 . "SOLAR") (62 . 7) (370 . 13) (100 . "AcDbLine") (10 10870.6636538462
8178.7330316742 0.0) (11 10867.575418552 8165.4977375566 0.0))
((0 . "LINE") (100 . "AcDbEntity") (8 . "SOLAR") (62 . 7) (370 . 13) (100 . "AcDbLine") (10 10867.575418552
8165.4977375566 0.0) (11 10854.4108257919 8109.0780542986 0.0))
((0 . "LINE") (100 . "AcDbEntity") (8 . "SOLAR") (62 . 7) (370 . 13) (100 . "AcDbLine") (10 10854.4108257919
8109.0780542986 0.0) (11 10843.8791515837 8063.9423076923 0.0))
((0 . "LINE") (100 . "AcDbEntity") (8 . "SOLAR") (62 . 7) (370 . 13) (100 . "AcDbLine") (10 10843.8791515837
8063.9423076923 0.0) (11 10836.3565271493 8031.7024886878 0.0))
((0 . "LINE") (100 . "AcDbEntity") (8 . "SOLAR") (62 . 7) (370 . 13) (100 . "AcDbLine") (10 10836.3565271493
8031.7024886878 0.0) (11 10828.4577714932 7997.850678733 0.0))
((0 . "LINE") (100 . "AcDbEntity") (8 . "SOLAR") (62 . 7) (370 . 13) (100 . "AcDbLine") (10 10828.4577714932
7997.850678733 0.0) (11 10818.3022285068 7954.3269230769 0.0))
((0 . "LINE") (100 . "AcDbEntity") (8 . "SOLAR") (62 . 7) (370 . 13) (100 . "AcDbLine") (10 10818.3022285068
7954.3269230769 0.0) (11 10809.6512104072 7917.2511312217 0.0))
((0 . "LINE") (100 . "AcDbEntity") (8 . "SOLAR") (62 . 7) (370 . 13) (100 . "AcDbLine") (10 10809.6512104072
7917.2511312217 0.0) (11 10807.3152375566 7907.2398190045 0.0))
((0 . "LINE") (100 . "AcDbEntity") (8 . "SOLAR") (62 . 7) (370 . 13) (100 . "AcDbLine") (10 11078.4313687783
8178.7330316742 0.0) (11 11074.0196040724 8165.4977375566 0.0))
((0 . "LINE") (100 . "AcDbEntity") (8 . "SOLAR") (62 . 7) (370 . 13) (100 . "AcDbLine") (10 11074.0196040724
8165.4977375566 0.0) (11 11055.2130429864 8109.0780542986 0.0))
((0 . "LINE") (100 . "AcDbEntity") (8 . "SOLAR") (62 . 7) (370 . 13) (100 . "AcDbLine") (10 11055.2130429864
8109.0780542986 0.0) (11 11040.1677941176 8063.9423076923 0.0))
((0 . "LINE") (100 . "AcDbEntity") (8 . "SOLAR") (62 . 7) (370 . 13) (100 . "AcDbLine") (10 11040.1677941176
8063.9423076923 0.0) (11 11029.4211877828 8031.7024886878 0.0))
((0 . "LINE") (100 . "AcDbEntity") (8 . "SOLAR") (62 . 7) (370 . 13) (100 . "AcDbLine") (10 11029.4211877828
8031.7024886878 0.0) (11 11018.1372511312 7997.850678733 0.0))
((0 . "LINE") (100 . "AcDbEntity") (8 . "SOLAR") (62 . 7) (370 . 13) (100 . "AcDbLine") (10 11018.1372511312
7997.850678733 0.0) (11 11003.6293325792 7954.3269230769 0.0))
((0 . "LINE") (100 . "AcDbEntity") (8 . "SOLAR") (62 . 7) (370 . 13) (100 . "AcDbLine") (10 11003.6293325792
7954.3269230769 0.0) (11 10991.2707352941 7917.2511312217 0.0))
((0 . "LINE") (100 . "AcDbEntity") (8 . "SOLAR") (62 . 7) (370 . 13) (100 . "AcDbLine") (10 10991.2707352941
7917.2511312217 0.0) (11 10987.9336312217 7907.2398190045 0.0))
((0 . "LINE") (100 . "AcDbEntity") (8 . "SOLAR") (62 . 7) (370 . 13) (100 . "AcDbLine") (10 10676.6145361991
8165.4977375566 0.0) (11 10867.575418552 8165.4977375566 0.0))
((0 . "LINE") (100 . "AcDbEntity") (8 . "SOLAR") (62 . 7) (370 . 13) (100 . "AcDbLine") (10 10867.575418552
8165.4977375566 0.0) (11 11074.0196040724 8165.4977375566 0.0))
((0 . "LINE") (100 . "AcDbEntity") (8 . "SOLAR") (62 . 7) (370 . 13) (100 . "AcDbLine") (10 11074.0196040724
8165.4977375566 0.0) (11 11264.9804864253 8165.4977375566 0.0))
((0 . "LINE") (100 . "AcDbEntity") (8 . "SOLAR") (62 . 7) (370 . 13) (100 . "AcDbLine") (10 10668.6687669683
8109.0780542986 0.0) (11 10854.4108257919 8109.0780542986 0.0))
((0 . "LINE") (100 . "AcDbEntity") (8 . "SOLAR") (62 . 7) (370 . 13) (100 . "AcDbLine") (10 10854.4108257919
8109.0780542986 0.0) (11 11055.2130429864 8109.0780542986 0.0))
((0 . "LINE") (100 . "AcDbEntity") (8 . "SOLAR") (62 . 7) (370 . 13) (100 . "AcDbLine") (10 11055.2130429864
8109.0780542986 0.0) (11 11240.95510181 8109.0780542986 0.0))
((0 . "LINE") (100 . "AcDbEntity") (8 . "SOLAR") (62 . 7) (370 . 13) (100 . "AcDbLine") (10 10662.3121493213
8063.9423076923 0.0) (11 10843.8791515837 8063.9423076923 0.0))
((0 . "LINE") (100 . "AcDbEntity") (8 . "SOLAR") (62 . 7) (370 . 13) (100 . "AcDbLine") (10 10843.8791515837
8063.9423076923 0.0) (11 11040.1677941176 8063.9423076923 0.0))
((0 . "LINE") (100 . "AcDbEntity") (8 . "SOLAR") (62 . 7) (370 . 13) (100 . "AcDbLine") (10 11040.1677941176
8063.9423076923 0.0) (11 11221.7347963801 8063.9423076923 0.0))
((0 . "LINE") (100 . "AcDbEntity") (8 . "SOLAR") (62 . 7) (370 . 13) (100 . "AcDbLine") (10 10657.7717081448
8031.7024886878 0.0) (11 10836.3565271493 8031.7024886878 0.0))
((0 . "LINE") (100 . "AcDbEntity") (8 . "SOLAR") (62 . 7) (370 . 13) (100 . "AcDbLine") (10 10836.3565271493
8031.7024886878 0.0) (11 11029.4211877828 8031.7024886878 0.0))
((0 . "LINE") (100 . "AcDbEntity") (8 . "SOLAR") (62 . 7) (370 . 13) (100 . "AcDbLine") (10 11029.4211877828
8031.7024886878 0.0) (11 11208.0060067873 8031.7024886878 0.0))
((0 . "LINE") (100 . "AcDbEntity") (8 . "SOLAR") (62 . 7) (370 . 13) (100 . "AcDbLine") (10 10653.0042420814
7997.850678733 0.0) (11 10828.4577714932 7997.850678733 0.0))
((0 . "LINE") (100 . "AcDbEntity") (8 . "SOLAR") (62 . 7) (370 . 13) (100 . "AcDbLine") (10 10828.4577714932
7997.850678733 0.0) (11 11018.1372511312 7997.850678733 0.0))
((0 . "LINE") (100 . "AcDbEntity") (8 . "SOLAR") (62 . 7) (370 . 13) (100 . "AcDbLine") (10 11018.1372511312
7997.850678733 0.0) (11 11193.590780543 7997.850678733 0.0))
((0 . "LINE") (100 . "AcDbEntity") (8 . "SOLAR") (62 . 7) (370 . 13) (100 . "AcDbLine") (10 10646.8746493213
7954.3269230769 0.0) (11 10818.3022285068 7954.3269230769 0.0))
((0 . "LINE") (100 . "AcDbEntity") (8 . "SOLAR") (62 . 7) (370 . 13) (100 . "AcDbLine") (10 10818.3022285068
7954.3269230769 0.0) (11 11003.6293325792 7954.3269230769 0.0))
((0 . "LINE") (100 . "AcDbEntity") (8 . "SOLAR") (62 . 7) (370 . 13) (100 . "AcDbLine") (10 11003.6293325792
7954.3269230769 0.0) (11 11175.0569117647 7954.3269230769 0.0))
((0 . "LINE") (100 . "AcDbEntity") (8 . "SOLAR") (62 . 7) (370 . 13) (100 . "AcDbLine") (10 10641.6531334842
7917.2511312217 0.0) (11 10809.6512104072 7917.2511312217 0.0))
((0 . "LINE") (100 . "AcDbEntity") (8 . "SOLAR") (62 . 7) (370 . 13) (100 . "AcDbLine") (10 10809.6512104072
7917.2511312217 0.0) (11 10991.2707352941 7917.2511312217 0.0))
((0 . "LINE") (100 . "AcDbEntity") (8 . "SOLAR") (62 . 7) (370 . 13) (100 . "AcDbLine") (10 10991.2707352941
7917.2511312217 0.0) (11 11159.268800905 7917.2511312217 0.0))
((0 . "LINE") (100 . "AcDbEntity") (8 . "SOLAR") (62 . 7) (370 . 13) (100 . "AcDbLine") (10 11346.1538461538
8212.6696832579 0.0) (11 12149.3212669683 8212.6696832579 0.0))
((0 . "LINE") (100 . "AcDbEntity") (8 . "SOLAR") (62 . 7) (370 . 13) (100 . "AcDbLine") (10 12149.3212669683
8212.6696832579 0.0) (11 11945.7013574661 7873.3031674208 0.0))
((0 . "LINE") (100 . "AcDbEntity") (8 . "SOLAR") (62 . 7) (370 . 13) (100 . "AcDbLine") (10 11945.7013574661
7873.3031674208 0.0) (11 11199.0950226244 7873.3031674208 0.0))
((0 . "LINE") (100 . "AcDbEntity") (8 . "SOLAR") (62 . 7) (370 . 13) (100 . "AcDbLine") (10 11199.0950226244
7873.3031674208 0.0) (11 11346.1538461538 8212.6696832579 0.0))
((0 . "LINE") (100 . "AcDbEntity") (8 . "SOLAR") (62 . 7) (370 . 13) (100 . "AcDbLine") (10 11351.3857466063
8178.7330316742 0.0) (11 11597.2850678733 8178.7330316742 0.0))
((0 . "LINE") (100 . "AcDbEntity") (8 . "SOLAR") (62 . 7) (370 . 13) (100 . "AcDbLine") (10 11597.2850678733
8178.7330316742 0.0) (11 11863.1221719457 8178.7330316742 0.0))
((0 . "LINE") (100 . "AcDbEntity") (8 . "SOLAR") (62 . 7) (370 . 13) (100 . "AcDbLine") (10 11863.1221719457
8178.7330316742 0.0) (11 12109.0214932127 8178.7330316742 0.0))
((0 . "LINE") (100 . "AcDbEntity") (8 . "SOLAR") (62 . 7) (370 . 13) (100 . "AcDbLine") (10 12109.0214932127
8178.7330316742 0.0) (11 12101.1354638009 8165.4977375566 0.0))
((0 . "LINE") (100 . "AcDbEntity") (8 . "SOLAR") (62 . 7) (370 . 13) (100 . "AcDbLine") (10 12101.1354638009
8165.4977375566 0.0) (11 12067.5187330317 8109.0780542986 0.0))
((0 . "LINE") (100 . "AcDbEntity") (8 . "SOLAR") (62 . 7) (370 . 13) (100 . "AcDbLine") (10 12067.5187330317
8109.0780542986 0.0) (11 12039.6648755656 8062.3303167421 0.0))
((0 . "LINE") (100 . "AcDbEntity") (8 . "SOLAR") (62 . 7) (370 . 13) (100 . "AcDbLine") (10 12039.6648755656
8062.3303167421 0.0) (11 12021.4157918552 8031.7024886878 0.0))
((0 . "LINE") (100 . "AcDbEntity") (8 . "SOLAR") (62 . 7) (370 . 13) (100 . "AcDbLine") (10 12021.4157918552
8031.7024886878 0.0) (11 12001.2457579186 7997.850678733 0.0))
((0 . "LINE") (100 . "AcDbEntity") (8 . "SOLAR") (62 . 7) (370 . 13) (100 . "AcDbLine") (10 12001.2457579186
7997.850678733 0.0) (11 11975.3128506787 7954.3269230769 0.0))
((0 . "LINE") (100 . "AcDbEntity") (8 . "SOLAR") (62 . 7) (370 . 13) (100 . "AcDbLine") (10 11975.3128506787
7954.3269230769 0.0) (11 11947.2567873303 7907.2398190045 0.0))
((0 . "LINE") (100 . "AcDbEntity") (8 . "SOLAR") (62 . 7) (370 . 13) (100 . "AcDbLine") (10 11947.2567873303
7907.2398190045 0.0) (11 11715.3091968326 7907.2398190045 0.0))
((0 . "LINE") (100 . "AcDbEntity") (8 . "SOLAR") (62 . 7) (370 . 13) (100 . "AcDbLine") (10 11715.3091968326
7907.2398190045 0.0) (11 11464.5550565611 7907.2398190045 0.0))
((0 . "LINE") (100 . "AcDbEntity") (8 . "SOLAR") (62 . 7) (370 . 13) (100 . "AcDbLine") (10 11464.5550565611
7907.2398190045 0.0) (11 11232.6074660633 7907.2398190045 0.0))
((0 . "LINE") (100 . "AcDbEntity") (8 . "SOLAR") (62 . 7) (370 . 13) (100 . "AcDbLine") (10 11232.6074660633
7907.2398190045 0.0) (11 11253.2080769231 7954.3269230769 0.0))
((0 . "LINE") (100 . "AcDbEntity") (8 . "SOLAR") (62 . 7) (370 . 13) (100 . "AcDbLine") (10 11253.2080769231
7954.3269230769 0.0) (11 11272.2497171946 7997.850678733 0.0))
((0 . "LINE") (100 . "AcDbEntity") (8 . "SOLAR") (62 . 7) (370 . 13) (100 . "AcDbLine") (10 11272.2497171946
7997.850678733 0.0) (11 11287.0598868778 8031.7024886878 0.0))
((0 . "LINE") (100 . "AcDbEntity") (8 . "SOLAR") (62 . 7) (370 . 13) (100 . "AcDbLine") (10 11287.0598868778
8031.7024886878 0.0) (11 11300.4595588235 8062.3303167421 0.0))
((0 . "LINE") (100 . "AcDbEntity") (8 . "SOLAR") (62 . 7) (370 . 13) (100 . "AcDbLine") (10 11300.4595588235
8062.3303167421 0.0) (11 11320.9116968326 8109.0780542986 0.0))
((0 . "LINE") (100 . "AcDbEntity") (8 . "SOLAR") (62 . 7) (370 . 13) (100 . "AcDbLine") (10 11320.9116968326
8109.0780542986 0.0) (11 11345.5953054299 8165.4977375566 0.0))
((0 . "LINE") (100 . "AcDbEntity") (8 . "SOLAR") (62 . 7) (370 . 13) (100 . "AcDbLine") (10 11345.5953054299
8165.4977375566 0.0) (11 11351.3857466063 8178.7330316742 0.0))
((0 . "LINE") (100 . "AcDbEntity") (8 . "SOLAR") (62 . 7) (370 . 13) (100 . "AcDbLine") (10 11597.2850678733
8178.7330316742 0.0) (11 11590.814479638 8165.4977375566 0.0))
((0 . "LINE") (100 . "AcDbEntity") (8 . "SOLAR") (62 . 7) (370 . 13) (100 . "AcDbLine") (10 11590.814479638
8165.4977375566 0.0) (11 11563.2315271493 8109.0780542986 0.0))
((0 . "LINE") (100 . "AcDbEntity") (8 . "SOLAR") (62 . 7) (370 . 13) (100 . "AcDbLine") (10 11563.2315271493
8109.0780542986 0.0) (11 11540.3770701357 8062.3303167421 0.0))
((0 . "LINE") (100 . "AcDbEntity") (8 . "SOLAR") (62 . 7) (370 . 13) (100 . "AcDbLine") (10 11540.3770701357
8062.3303167421 0.0) (11 11525.4034728507 8031.7024886878 0.0))
((0 . "LINE") (100 . "AcDbEntity") (8 . "SOLAR") (62 . 7) (370 . 13) (100 . "AcDbLine") (10 11525.4034728507
8031.7024886878 0.0) (11 11508.853699095 7997.850678733 0.0))
((0 . "LINE") (100 . "AcDbEntity") (8 . "SOLAR") (62 . 7) (370 . 13) (100 . "AcDbLine") (10 11508.853699095
7997.850678733 0.0) (11 11487.575418552 7954.3269230769 0.0))
((0 . "LINE") (100 . "AcDbEntity") (8 . "SOLAR") (62 . 7) (370 . 13) (100 . "AcDbLine") (10 11487.575418552
7954.3269230769 0.0) (11 11464.5550565611 7907.2398190045 0.0))
((0 . "LINE") (100 . "AcDbEntity") (8 . "SOLAR") (62 . 7) (370 . 13) (100 . "AcDbLine") (10 11863.1221719457
8178.7330316742 0.0) (11 11855.9162895928 8165.4977375566 0.0))
((0 . "LINE") (100 . "AcDbEntity") (8 . "SOLAR") (62 . 7) (370 . 13) (100 . "AcDbLine") (10 11855.9162895928
8165.4977375566 0.0) (11 11825.1989027149 8109.0780542986 0.0))
((0 . "LINE") (100 . "AcDbEntity") (8 . "SOLAR") (62 . 7) (370 . 13) (100 . "AcDbLine") (10 11825.1989027149
8109.0780542986 0.0) (11 11799.7473642534 8062.3303167421 0.0))
((0 . "LINE") (100 . "AcDbEntity") (8 . "SOLAR") (62 . 7) (370 . 13) (100 . "AcDbLine") (10 11799.7473642534
8062.3303167421 0.0) (11 11783.0722058824 8031.7024886878 0.0))
((0 . "LINE") (100 . "AcDbEntity") (8 . "SOLAR") (62 . 7) (370 . 13) (100 . "AcDbLine") (10 11783.0722058824
8031.7024886878 0.0) (11 11764.6417760181 7997.850678733 0.0))
((0 . "LINE") (100 . "AcDbEntity") (8 . "SOLAR") (62 . 7) (370 . 13) (100 . "AcDbLine") (10 11764.6417760181
7997.850678733 0.0) (11 11740.9455090498 7954.3269230769 0.0))
((0 . "LINE") (100 . "AcDbEntity") (8 . "SOLAR") (62 . 7) (370 . 13) (100 . "AcDbLine") (10 11740.9455090498
7954.3269230769 0.0) (11 11715.3091968326 7907.2398190045 0.0))
((0 . "LINE") (100 . "AcDbEntity") (8 . "SOLAR") (62 . 7) (370 . 13) (100 . "AcDbLine") (10 11345.5953054299
8165.4977375566 0.0) (11 11590.814479638 8165.4977375566 0.0))
((0 . "LINE") (100 . "AcDbEntity") (8 . "SOLAR") (62 . 7) (370 . 13) (100 . "AcDbLine") (10 11590.814479638
8165.4977375566 0.0) (11 11855.9162895928 8165.4977375566 0.0))
((0 . "LINE") (100 . "AcDbEntity") (8 . "SOLAR") (62 . 7) (370 . 13) (100 . "AcDbLine") (10 11855.9162895928
8165.4977375566 0.0) (11 12101.1354638009 8165.4977375566 0.0))
((0 . "LINE") (100 . "AcDbEntity") (8 . "SOLAR") (62 . 7) (370 . 13) (100 . "AcDbLine") (10 11320.9116968326
8109.0780542986 0.0) (11 11563.2315271493 8109.0780542986 0.0))
((0 . "LINE") (100 . "AcDbEntity") (8 . "SOLAR") (62 . 7) (370 . 13) (100 . "AcDbLine") (10 11563.2315271493
8109.0780542986 0.0) (11 11825.1989027149 8109.0780542986 0.0))
((0 . "LINE") (100 . "AcDbEntity") (8 . "SOLAR") (62 . 7) (370 . 13) (100 . "AcDbLine") (10 11825.1989027149
8109.0780542986 0.0) (11 12067.5187330317 8109.0780542986 0.0))
((0 . "LINE") (100 . "AcDbEntity") (8 . "SOLAR") (62 . 7) (370 . 13) (100 . "AcDbLine") (10 11300.4595588235
8062.3303167421 0.0) (11 11540.3770701357 8062.3303167421 0.0))
((0 . "LINE") (100 . "AcDbEntity") (8 . "SOLAR") (62 . 7) (370 . 13) (100 . "AcDbLine") (10 11540.3770701357
8062.3303167421 0.0) (11 11799.7473642534 8062.3303167421 0.0))
((0 . "LINE") (100 . "AcDbEntity") (8 . "SOLAR") (62 . 7) (370 . 13) (100 . "AcDbLine") (10 11799.7473642534
8062.3303167421 0.0) (11 12039.6648755656 8062.3303167421 0.0))
((0 . "LINE") (100 . "AcDbEntity") (8 . "SOLAR") (62 . 7) (370 . 13) (100 . "AcDbLine") (10 11287.0598868778
8031.7024886878 0.0) (11 11525.4034728507 8031.7024886878 0.0))
((0 . "LINE") (100 . "AcDbEntity") (8 . "SOLAR") (62 . 7) (370 . 13) (100 . "AcDbLine") (10 11525.4034728507
8031.7024886878 0.0) (11 11783.0722058824 8031.7024886878 0.0))
((0 . "LINE") (100 . "AcDbEntity") (8 . "SOLAR") (62 . 7) (370 . 13) (100 . "AcDbLine") (10 11783.0722058824
8031.7024886878 0.0) (11 12021.4157918552 8031.7024886878 0.0))
((0 . "LINE") (100 . "AcDbEntity") (8 . "SOLAR") (62 . 7) (370 . 13) (100 . "AcDbLine") (10 11272.2497171946
7997.850678733 0.0) (11 11508.853699095 7997.850678733 0.0))
((0 . "LINE") (100 . "AcDbEntity") (8 . "SOLAR") (62 . 7) (370 . 13) (100 . "AcDbLine") (10 11508.853699095
7997.850678733 0.0) (11 11764.6417760181 7997.850678733 0.0))
((0 . "LINE") (100 . "AcDbEntity") (8 . "SOLAR") (62 . 7) (370 . 13) (100 . "AcDbLine") (10 11764.6417760181
7997.850678733 0.0) (11 12001.2457579186 7997.850678733 0.0))
((0 . "LINE") (100 . "AcDbEntity") (8 . "SOLAR") (62 . 7) (370 . 13) (100 . "AcDbLine") (10 11253.2080769231
7954.3269230769 0.0) (11 11487.575418552 7954.3269230769 0.0))
((0 . "LINE") (100 . "AcDbEntity") (8 . "SOLAR") (62 . 7) (370 . 13) (100 . "AcDbLine") (10 11487.575418552
7954.3269230769 0.0) (11 11740.9455090498 7954.3269230769 0.0))
((0 . "LINE") (100 . "AcDbEntity") (8 . "SOLAR") (62 . 7) (370 . 13) (100 . "AcDbLine") (10 11740.9455090498
7954.3269230769 0.0) (11 11975.3128506787 7954.3269230769 0.0))
((0 . "LINE") (100 . "AcDbEntity") (8 . "SOLAR") (62 . 7) (370 . 13) (100 . "AcDbLine") (10 12522.6244343891
8212.6696832579 0.0) (11 13212.6696832579 8212.6696832579 0.0))
((0 . "LINE") (100 . "AcDbEntity") (8 . "SOLAR") (62 . 7) (370 . 13) (100 . "AcDbLine") (10 13212.6696832579
8212.6696832579 0.0) (11 12986.4253393665 7873.3031674208 0.0))
((0 . "LINE") (100 . "AcDbEntity") (8 . "SOLAR") (62 . 7) (370 . 13) (100 . "AcDbLine") (10 12986.4253393665
7873.3031674208 0.0) (11 12319.0045248869 7873.3031674208 0.0))
((0 . "LINE") (100 . "AcDbEntity") (8 . "SOLAR") (62 . 7) (370 . 13) (100 . "AcDbLine") (10 12319.0045248869
7873.3031674208 0.0) (11 12522.6244343891 8212.6696832579 0.0))
((0 . "LINE") (100 . "AcDbEntity") (8 . "SOLAR") (62 . 7) (370 . 13) (100 . "AcDbLine") (10 12519.4570135747
8178.7330316742 0.0) (11 12731.5233823529 8178.7330316742 0.0))
((0 . "LINE") (100 . "AcDbEntity") (8 . "SOLAR") (62 . 7) (370 . 13) (100 . "AcDbLine") (10 12731.5233823529
8178.7330316742 0.0) (11 12960.7843099547 8178.7330316742 0.0))
((0 . "LINE") (100 . "AcDbEntity") (8 . "SOLAR") (62 . 7) (370 . 13) (100 . "AcDbLine") (10 12960.7843099547
8178.7330316742 0.0) (11 13172.850678733 8178.7330316742 0.0))
((0 . "LINE") (100 . "AcDbEntity") (8 . "SOLAR") (62 . 7) (370 . 13) (100 . "AcDbLine") (10 13172.850678733
8178.7330316742 0.0) (11 13164.0492081448 8165.4977375566 0.0))
((0 . "LINE") (100 . "AcDbEntity") (8 . "SOLAR") (62 . 7) (370 . 13) (100 . "AcDbLine") (10 13164.0492081448
8165.4977375566 0.0) (11 13125.4581447964 8107.4660633484 0.0))
((0 . "LINE") (100 . "AcDbEntity") (8 . "SOLAR") (62 . 7) (370 . 13) (100 . "AcDbLine") (10 13125.4581447964
8107.4660633484 0.0) (11 13096.5148529412 8063.9423076923 0.0))
((0 . "LINE") (100 . "AcDbEntity") (8 . "SOLAR") (62 . 7) (370 . 13) (100 . "AcDbLine") (10 13096.5148529412
8063.9423076923 0.0) (11 13066.4995701357 8018.806561086 0.0))
((0 . "LINE") (100 . "AcDbEntity") (8 . "SOLAR") (62 . 7) (370 . 13) (100 . "AcDbLine") (10 13066.4995701357
8018.806561086 0.0) (11 13037.5562782805 7975.2828054299 0.0))
((0 . "LINE") (100 . "AcDbEntity") (8 . "SOLAR") (62 . 7) (370 . 13) (100 . "AcDbLine") (10 13037.5562782805
7975.2828054299 0.0) (11 13016.1167986425 7943.0429864253 0.0))
((0 . "LINE") (100 . "AcDbEntity") (8 . "SOLAR") (62 . 7) (370 . 13) (100 . "AcDbLine") (10 13016.1167986425
7943.0429864253 0.0) (11 12992.3076923077 7907.2398190045 0.0))
((0 . "LINE") (100 . "AcDbEntity") (8 . "SOLAR") (62 . 7) (370 . 13) (100 . "AcDbLine") (10 12992.3076923077
7907.2398190045 0.0) (11 12785.8220248869 7907.2398190045 0.0))
((0 . "LINE") (100 . "AcDbEntity") (8 . "SOLAR") (62 . 7) (370 . 13) (100 . "AcDbLine") (10 12785.8220248869
7907.2398190045 0.0) (11 12562.5942647059 7907.2398190045 0.0))
((0 . "LINE") (100 . "AcDbEntity") (8 . "SOLAR") (62 . 7) (370 . 13) (100 . "AcDbLine") (10 12562.5942647059
7907.2398190045 0.0) (11 12356.1085972851 7907.2398190045 0.0))
((0 . "LINE") (100 . "AcDbEntity") (8 . "SOLAR") (62 . 7) (370 . 13) (100 . "AcDbLine") (10 12356.1085972851
7907.2398190045 0.0) (11 12377.6501696833 7943.0429864253 0.0))
((0 . "LINE") (100 . "AcDbEntity") (8 . "SOLAR") (62 . 7) (370 . 13) (100 . "AcDbLine") (10 12377.6501696833
7943.0429864253 0.0) (11 12397.0477941176 7975.2828054299 0.0))
((0 . "LINE") (100 . "AcDbEntity") (8 . "SOLAR") (62 . 7) (370 . 13) (100 . "AcDbLine") (10 12397.0477941176
7975.2828054299 0.0) (11 12423.2345927602 8018.806561086 0.0))
((0 . "LINE") (100 . "AcDbEntity") (8 . "SOLAR") (62 . 7) (370 . 13) (100 . "AcDbLine") (10 12423.2345927602
8018.806561086 0.0) (11 12450.3912669683 8063.9423076923 0.0))
((0 . "LINE") (100 . "AcDbEntity") (8 . "SOLAR") (62 . 7) (370 . 13) (100 . "AcDbLine") (10 12450.3912669683
8063.9423076923 0.0) (11 12476.5780542986 8107.4660633484 0.0))
((0 . "LINE") (100 . "AcDbEntity") (8 . "SOLAR") (62 . 7) (370 . 13) (100 . "AcDbLine") (10 12476.5780542986
8107.4660633484 0.0) (11 12511.4937782805 8165.4977375566 0.0))
((0 . "LINE") (100 . "AcDbEntity") (8 . "SOLAR") (62 . 7) (370 . 13) (100 . "AcDbLine") (10 12511.4937782805
8165.4977375566 0.0) (11 12519.4570135747 8178.7330316742 0.0))
((0 . "LINE") (100 . "AcDbEntity") (8 . "SOLAR") (62 . 7) (370 . 13) (100 . "AcDbLine") (10 12731.5233823529
8178.7330316742 0.0) (11 12723.2880882353 8165.4977375566 0.0))
((0 . "LINE") (100 . "AcDbEntity") (8 . "SOLAR") (62 . 7) (370 . 13) (100 . "AcDbLine") (10 12723.2880882353
8165.4977375566 0.0) (11 12687.1794909502 8107.4660633484 0.0))
((0 . "LINE") (100 . "AcDbEntity") (8 . "SOLAR") (62 . 7) (370 . 13) (100 . "AcDbLine") (10 12687.1794909502
8107.4660633484 0.0) (11 12660.0980429864 8063.9423076923 0.0))
((0 . "LINE") (100 . "AcDbEntity") (8 . "SOLAR") (62 . 7) (370 . 13) (100 . "AcDbLine") (10 12660.0980429864
8063.9423076923 0.0) (11 12632.0135746606 8018.806561086 0.0))
((0 . "LINE") (100 . "AcDbEntity") (8 . "SOLAR") (62 . 7) (370 . 13) (100 . "AcDbLine") (10 12632.0135746606
8018.806561086 0.0) (11 12604.9321266968 7975.2828054299 0.0))
((0 . "LINE") (100 . "AcDbEntity") (8 . "SOLAR") (62 . 7) (370 . 13) (100 . "AcDbLine") (10 12604.9321266968
7975.2828054299 0.0) (11 12584.8717986425 7943.0429864253 0.0))
((0 . "LINE") (100 . "AcDbEntity") (8 . "SOLAR") (62 . 7) (370 . 13) (100 . "AcDbLine") (10 12584.8717986425
7943.0429864253 0.0) (11 12562.5942647059 7907.2398190045 0.0))
((0 . "LINE") (100 . "AcDbEntity") (8 . "SOLAR") (62 . 7) (370 . 13) (100 . "AcDbLine") (10 12960.7843099547
8178.7330316742 0.0) (11 12952.25489819 8165.4977375566 0.0))
((0 . "LINE") (100 . "AcDbEntity") (8 . "SOLAR") (62 . 7) (370 . 13) (100 . "AcDbLine") (10 12952.25489819
8165.4977375566 0.0) (11 12914.8567081448 8107.4660633484 0.0))
((0 . "LINE") (100 . "AcDbEntity") (8 . "SOLAR") (62 . 7) (370 . 13) (100 . "AcDbLine") (10 12914.8567081448
8107.4660633484 0.0) (11 12886.8080656109 8063.9423076923 0.0))
((0 . "LINE") (100 . "AcDbEntity") (8 . "SOLAR") (62 . 7) (370 . 13) (100 . "AcDbLine") (10 12886.8080656109
8063.9423076923 0.0) (11 12857.7205882353 8018.806561086 0.0))
((0 . "LINE") (100 . "AcDbEntity") (8 . "SOLAR") (62 . 7) (370 . 13) (100 . "AcDbLine") (10 12857.7205882353
8018.806561086 0.0) (11 12829.6719457014 7975.2828054299 0.0))
((0 . "LINE") (100 . "AcDbEntity") (8 . "SOLAR") (62 . 7) (370 . 13) (100 . "AcDbLine") (10 12829.6719457014
7975.2828054299 0.0) (11 12808.8951696833 7943.0429864253 0.0))
((0 . "LINE") (100 . "AcDbEntity") (8 . "SOLAR") (62 . 7) (370 . 13) (100 . "AcDbLine") (10 12808.8951696833
7943.0429864253 0.0) (11 12785.8220248869 7907.2398190045 0.0))
((0 . "LINE") (100 . "AcDbEntity") (8 . "SOLAR") (62 . 7) (370 . 13) (100 . "AcDbLine") (10 12511.4937782805
8165.4977375566 0.0) (11 12723.2880882353 8165.4977375566 0.0))
((0 . "LINE") (100 . "AcDbEntity") (8 . "SOLAR") (62 . 7) (370 . 13) (100 . "AcDbLine") (10 12723.2880882353
8165.4977375566 0.0) (11 12952.25489819 8165.4977375566 0.0))
((0 . "LINE") (100 . "AcDbEntity") (8 . "SOLAR") (62 . 7) (370 . 13) (100 . "AcDbLine") (10 12952.25489819
8165.4977375566 0.0) (11 13164.0492081448 8165.4977375566 0.0))
((0 . "LINE") (100 . "AcDbEntity") (8 . "SOLAR") (62 . 7) (370 . 13) (100 . "AcDbLine") (10 12476.5780542986
8107.4660633484 0.0) (11 12687.1794909502 8107.4660633484 0.0))
((0 . "LINE") (100 . "AcDbEntity") (8 . "SOLAR") (62 . 7) (370 . 13) (100 . "AcDbLine") (10 12687.1794909502
8107.4660633484 0.0) (11 12914.8567081448 8107.4660633484 0.0))
((0 . "LINE") (100 . "AcDbEntity") (8 . "SOLAR") (62 . 7) (370 . 13) (100 . "AcDbLine") (10 12914.8567081448
8107.4660633484 0.0) (11 13125.4581447964 8107.4660633484 0.0))
((0 . "LINE") (100 . "AcDbEntity") (8 . "SOLAR") (62 . 7) (370 . 13) (100 . "AcDbLine") (10 12450.3912669683
8063.9423076923 0.0) (11 12660.0980429864 8063.9423076923 0.0))
((0 . "LINE") (100 . "AcDbEntity") (8 . "SOLAR") (62 . 7) (370 . 13) (100 . "AcDbLine") (10 12660.0980429864
8063.9423076923 0.0) (11 12886.8080656109 8063.9423076923 0.0))
((0 . "LINE") (100 . "AcDbEntity") (8 . "SOLAR") (62 . 7) (370 . 13) (100 . "AcDbLine") (10 12886.8080656109
8063.9423076923 0.0) (11 13096.5148529412 8063.9423076923 0.0))
((0 . "LINE") (100 . "AcDbEntity") (8 . "SOLAR") (62 . 7) (370 . 13) (100 . "AcDbLine") (10 12423.2345927602
8018.806561086 0.0) (11 12632.0135746606 8018.806561086 0.0))
((0 . "LINE") (100 . "AcDbEntity") (8 . "SOLAR") (62 . 7) (370 . 13) (100 . "AcDbLine") (10 12632.0135746606
8018.806561086 0.0) (11 12857.7205882353 8018.806561086 0.0))
((0 . "LINE") (100 . "AcDbEntity") (8 . "SOLAR") (62 . 7) (370 . 13) (100 . "AcDbLine") (10 12857.7205882353
8018.806561086 0.0) (11 13066.4995701357 8018.806561086 0.0))
((0 . "LINE") (100 . "AcDbEntity") (8 . "SOLAR") (62 . 7) (370 . 13) (100 . "AcDbLine") (10 12397.0477941176
7975.2828054299 0.0) (11 12604.9321266968 7975.2828054299 0.0))
((0 . "LINE") (100 . "AcDbEntity") (8 . "SOLAR") (62 . 7) (370 . 13) (100 . "AcDbLine") (10 12604.9321266968
7975.2828054299 0.0) (11 12829.6719457014 7975.2828054299 0.0))
((0 . "LINE") (100 . "AcDbEntity") (8 . "SOLAR") (62 . 7) (370 . 13) (100 . "AcDbLine") (10 12829.6719457014
7975.2828054299 0.0) (11 13037.5562782805 7975.2828054299 0.0))
((0 . "LINE") (100 . "AcDbEntity") (8 . "SOLAR") (62 . 7) (370 . 13) (100 . "AcDbLine") (10 12377.6501696833
7943.0429864253 0.0) (11 12584.8717986425 7943.0429864253 0.0))
((0 . "LINE") (100 . "AcDbEntity") (8 . "SOLAR") (62 . 7) (370 . 13) (100 . "AcDbLine") (10 12584.8717986425
7943.0429864253 0.0) (11 12808.8951696833 7943.0429864253 0.0))
((0 . "LINE") (100 . "AcDbEntity") (8 . "SOLAR") (62 . 7) (370 . 13) (100 . "AcDbLine") (10 12808.8951696833
7943.0429864253 0.0) (11 13016.1167986425 7943.0429864253 0.0))
((0 . "LINE") (100 . "AcDbEntity") (8 . "SOLAR") (62 . 7) (370 . 13) (100 . "AcDbLine") (10 13257.9185520362
8212.6696832579 0.0) (11 14027.149321267 8212.6696832579 0.0))
((0 . "LINE") (100 . "AcDbEntity") (8 . "SOLAR") (62 . 7) (370 . 13) (100 . "AcDbLine") (10 14027.149321267
8212.6696832579 0.0) (11 13823.5294117647 7873.3031674208 0.0))
((0 . "LINE") (100 . "AcDbEntity") (8 . "SOLAR") (62 . 7) (370 . 13) (100 . "AcDbLine") (10 13823.5294117647
7873.3031674208 0.0) (11 13031.6742081448 7873.3031674208 0.0))
((0 . "LINE") (100 . "AcDbEntity") (8 . "SOLAR") (62 . 7) (370 . 13) (100 . "AcDbLine") (10 13031.6742081448
7873.3031674208 0.0) (11 13257.9185520362 8212.6696832579 0.0))
((0 . "LINE") (100 . "AcDbEntity") (8 . "SOLAR") (62 . 7) (370 . 13) (100 . "AcDbLine") (10 13254.5814479638
8178.7330316742 0.0) (11 13492.4585180995 8178.7330316742 0.0))
((0 . "LINE") (100 . "AcDbEntity") (8 . "SOLAR") (62 . 7) (370 . 13) (100 . "AcDbLine") (10 13492.4585180995
8178.7330316742 0.0) (11 13749.6229298643 8178.7330316742 0.0))
((0 . "LINE") (100 . "AcDbEntity") (8 . "SOLAR") (62 . 7) (370 . 13) (100 . "AcDbLine") (10 13749.6229298643
8178.7330316742 0.0) (11 13987.5 8178.7330316742 0.0))
((0 . "LINE") (100 . "AcDbEntity") (8 . "SOLAR") (62 . 7) (370 . 13) (100 . "AcDbLine") (10 13987.5 8178.7330316742 0.0)
(11 13979.5367647059 8165.4977375566 0.0))
((0 . "LINE") (100 . "AcDbEntity") (8 . "SOLAR") (62 . 7) (370 . 13) (100 . "AcDbLine") (10 13979.5367647059
8165.4977375566 0.0) (11 13944.621040724 8107.4660633484 0.0))
((0 . "LINE") (100 . "AcDbEntity") (8 . "SOLAR") (62 . 7) (370 . 13) (100 . "AcDbLine") (10 13944.621040724
8107.4660633484 0.0) (11 13917.4643665158 8062.3303167421 0.0))
((0 . "LINE") (100 . "AcDbEntity") (8 . "SOLAR") (62 . 7) (370 . 13) (100 . "AcDbLine") (10 13917.4643665158
8062.3303167421 0.0) (11 13886.4281674208 8010.7466063348 0.0))
((0 . "LINE") (100 . "AcDbEntity") (8 . "SOLAR") (62 . 7) (370 . 13) (100 . "AcDbLine") (10 13886.4281674208
8010.7466063348 0.0) (11 13865.090780543 7975.2828054299 0.0))
((0 . "LINE") (100 . "AcDbEntity") (8 . "SOLAR") (62 . 7) (370 . 13) (100 . "AcDbLine") (10 13865.090780543
7975.2828054299 0.0) (11 13844.723280543 7941.4309954751 0.0))
((0 . "LINE") (100 . "AcDbEntity") (8 . "SOLAR") (62 . 7) (370 . 13) (100 . "AcDbLine") (10 13844.723280543
7941.4309954751 0.0) (11 13824.1515837104 7907.2398190045 0.0))
((0 . "LINE") (100 . "AcDbEntity") (8 . "SOLAR") (62 . 7) (370 . 13) (100 . "AcDbLine") (10 13824.1515837104
7907.2398190045 0.0) (11 13580.6938122172 7907.2398190045 0.0))
((0 . "LINE") (100 . "AcDbEntity") (8 . "SOLAR") (62 . 7) (370 . 13) (100 . "AcDbLine") (10 13580.6938122172
7907.2398190045 0.0) (11 13317.4962330317 7907.2398190045 0.0))
((0 . "LINE") (100 . "AcDbEntity") (8 . "SOLAR") (62 . 7) (370 . 13) (100 . "AcDbLine") (10 13317.4962330317
7907.2398190045 0.0) (11 13074.0384615385 7907.2398190045 0.0))
((0 . "LINE") (100 . "AcDbEntity") (8 . "SOLAR") (62 . 7) (370 . 13) (100 . "AcDbLine") (10 13074.0384615385
7907.2398190045 0.0) (11 13096.7755995475 7941.4309954751 0.0))
((0 . "LINE") (100 . "AcDbEntity") (8 . "SOLAR") (62 . 7) (370 . 13) (100 . "AcDbLine") (10 13096.7755995475
7941.4309954751 0.0) (11 13119.2870475113 7975.2828054299 0.0))
((0 . "LINE") (100 . "AcDbEntity") (8 . "SOLAR") (62 . 7) (370 . 13) (100 . "AcDbLine") (10 13119.2870475113
7975.2828054299 0.0) (11 13142.8704751131 8010.7466063348 0.0))
((0 . "LINE") (100 . "AcDbEntity") (8 . "SOLAR") (62 . 7) (370 . 13) (100 . "AcDbLine") (10 13142.8704751131
8010.7466063348 0.0) (11 13177.1736425339 8062.3303167421 0.0))
((0 . "LINE") (100 . "AcDbEntity") (8 . "SOLAR") (62 . 7) (370 . 13) (100 . "AcDbLine") (10 13177.1736425339
8062.3303167421 0.0) (11 13207.1889140272 8107.4660633484 0.0))
((0 . "LINE") (100 . "AcDbEntity") (8 . "SOLAR") (62 . 7) (370 . 13) (100 . "AcDbLine") (10 13207.1889140272
8107.4660633484 0.0) (11 13245.7799773756 8165.4977375566 0.0))
((0 . "LINE") (100 . "AcDbEntity") (8 . "SOLAR") (62 . 7) (370 . 13) (100 . "AcDbLine") (10 13245.7799773756
8165.4977375566 0.0) (11 13254.5814479638 8178.7330316742 0.0))
((0 . "LINE") (100 . "AcDbEntity") (8 . "SOLAR") (62 . 7) (370 . 13) (100 . "AcDbLine") (10 13492.4585180995
8178.7330316742 0.0) (11 13483.9291063348 8165.4977375566 0.0))
((0 . "LINE") (100 . "AcDbEntity") (8 . "SOLAR") (62 . 7) (370 . 13) (100 . "AcDbLine") (10 13483.9291063348
8165.4977375566 0.0) (11 13446.5309162896 8107.4660633484 0.0))
((0 . "LINE") (100 . "AcDbEntity") (8 . "SOLAR") (62 . 7) (370 . 13) (100 . "AcDbLine") (10 13446.5309162896
8107.4660633484 0.0) (11 13417.443438914 8062.3303167421 0.0))
((0 . "LINE") (100 . "AcDbEntity") (8 . "SOLAR") (62 . 7) (370 . 13) (100 . "AcDbLine") (10 13417.443438914
8062.3303167421 0.0) (11 13384.2005995475 8010.7466063348 0.0))
((0 . "LINE") (100 . "AcDbEntity") (8 . "SOLAR") (62 . 7) (370 . 13) (100 . "AcDbLine") (10 13384.2005995475
8010.7466063348 0.0) (11 13361.3461538462 7975.2828054299 0.0))
((0 . "LINE") (100 . "AcDbEntity") (8 . "SOLAR") (62 . 7) (370 . 13) (100 . "AcDbLine") (10 13361.3461538462
7975.2828054299 0.0) (11 13339.5305429864 7941.4309954751 0.0))
((0 . "LINE") (100 . "AcDbEntity") (8 . "SOLAR") (62 . 7) (370 . 13) (100 . "AcDbLine") (10 13339.5305429864
7941.4309954751 0.0) (11 13317.4962330317 7907.2398190045 0.0))
((0 . "LINE") (100 . "AcDbEntity") (8 . "SOLAR") (62 . 7) (370 . 13) (100 . "AcDbLine") (10 13749.6229298643
8178.7330316742 0.0) (11 13741.3876357466 8165.4977375566 0.0))
((0 . "LINE") (100 . "AcDbEntity") (8 . "SOLAR") (62 . 7) (370 . 13) (100 . "AcDbLine") (10 13741.3876357466
8165.4977375566 0.0) (11 13705.2790384615 8107.4660633484 0.0))
((0 . "LINE") (100 . "AcDbEntity") (8 . "SOLAR") (62 . 7) (370 . 13) (100 . "AcDbLine") (10 13705.2790384615
8107.4660633484 0.0) (11 13677.1945701357 8062.3303167421 0.0))
((0 . "LINE") (100 . "AcDbEntity") (8 . "SOLAR") (62 . 7) (370 . 13) (100 . "AcDbLine") (10 13677.1945701357
8062.3303167421 0.0) (11 13645.0980429864 8010.7466063348 0.0))
((0 . "LINE") (100 . "AcDbEntity") (8 . "SOLAR") (62 . 7) (370 . 13) (100 . "AcDbLine") (10 13645.0980429864
8010.7466063348 0.0) (11 13623.0316742081 7975.2828054299 0.0))
((0 . "LINE") (100 . "AcDbEntity") (8 . "SOLAR") (62 . 7) (370 . 13) (100 . "AcDbLine") (10 13623.0316742081
7975.2828054299 0.0) (11 13601.9683257919 7941.4309954751 0.0))
((0 . "LINE") (100 . "AcDbEntity") (8 . "SOLAR") (62 . 7) (370 . 13) (100 . "AcDbLine") (10 13601.9683257919
7941.4309954751 0.0) (11 13580.6938122172 7907.2398190045 0.0))
((0 . "LINE") (100 . "AcDbEntity") (8 . "SOLAR") (62 . 7) (370 . 13) (100 . "AcDbLine") (10 13245.7799773756
8165.4977375566 0.0) (11 13483.9291063348 8165.4977375566 0.0))
((0 . "LINE") (100 . "AcDbEntity") (8 . "SOLAR") (62 . 7) (370 . 13) (100 . "AcDbLine") (10 13483.9291063348
8165.4977375566 0.0) (11 13741.3876357466 8165.4977375566 0.0))
((0 . "LINE") (100 . "AcDbEntity") (8 . "SOLAR") (62 . 7) (370 . 13) (100 . "AcDbLine") (10 13741.3876357466
8165.4977375566 0.0) (11 13979.5367647059 8165.4977375566 0.0))
((0 . "LINE") (100 . "AcDbEntity") (8 . "SOLAR") (62 . 7) (370 . 13) (100 . "AcDbLine") (10 13207.1889140272
8107.4660633484 0.0) (11 13446.5309162896 8107.4660633484 0.0))
((0 . "LINE") (100 . "AcDbEntity") (8 . "SOLAR") (62 . 7) (370 . 13) (100 . "AcDbLine") (10 13446.5309162896
8107.4660633484 0.0) (11 13705.2790384615 8107.4660633484 0.0))
((0 . "LINE") (100 . "AcDbEntity") (8 . "SOLAR") (62 . 7) (370 . 13) (100 . "AcDbLine") (10 13705.2790384615
8107.4660633484 0.0) (11 13944.621040724 8107.4660633484 0.0))
((0 . "LINE") (100 . "AcDbEntity") (8 . "SOLAR") (62 . 7) (370 . 13) (100 . "AcDbLine") (10 13177.1736425339
8062.3303167421 0.0) (11 13417.443438914 8062.3303167421 0.0))
((0 . "LINE") (100 . "AcDbEntity") (8 . "SOLAR") (62 . 7) (370 . 13) (100 . "AcDbLine") (10 13417.443438914
8062.3303167421 0.0) (11 13677.1945701357 8062.3303167421 0.0))
((0 . "LINE") (100 . "AcDbEntity") (8 . "SOLAR") (62 . 7) (370 . 13) (100 . "AcDbLine") (10 13677.1945701357
8062.3303167421 0.0) (11 13917.4643665158 8062.3303167421 0.0))
((0 . "LINE") (100 . "AcDbEntity") (8 . "SOLAR") (62 . 7) (370 . 13) (100 . "AcDbLine") (10 13142.8704751131
8010.7466063348 0.0) (11 13384.2005995475 8010.7466063348 0.0))
((0 . "LINE") (100 . "AcDbEntity") (8 . "SOLAR") (62 . 7) (370 . 13) (100 . "AcDbLine") (10 13384.2005995475
8010.7466063348 0.0) (11 13645.0980429864 8010.7466063348 0.0))
((0 . "LINE") (100 . "AcDbEntity") (8 . "SOLAR") (62 . 7) (370 . 13) (100 . "AcDbLine") (10 13645.0980429864
8010.7466063348 0.0) (11 13886.4281674208 8010.7466063348 0.0))
((0 . "LINE") (100 . "AcDbEntity") (8 . "SOLAR") (62 . 7) (370 . 13) (100 . "AcDbLine") (10 13119.2870475113
7975.2828054299 0.0) (11 13361.3461538462 7975.2828054299 0.0))
((0 . "LINE") (100 . "AcDbEntity") (8 . "SOLAR") (62 . 7) (370 . 13) (100 . "AcDbLine") (10 13361.3461538462
7975.2828054299 0.0) (11 13623.0316742081 7975.2828054299 0.0))
((0 . "LINE") (100 . "AcDbEntity") (8 . "SOLAR") (62 . 7) (370 . 13) (100 . "AcDbLine") (10 13623.0316742081
7975.2828054299 0.0) (11 13865.090780543 7975.2828054299 0.0))
((0 . "LINE") (100 . "AcDbEntity") (8 . "SOLAR") (62 . 7) (370 . 13) (100 . "AcDbLine") (10 13096.7755995475
7941.4309954751 0.0) (11 13339.5305429864 7941.4309954751 0.0))
((0 . "LINE") (100 . "AcDbEntity") (8 . "SOLAR") (62 . 7) (370 . 13) (100 . "AcDbLine") (10 13339.5305429864
7941.4309954751 0.0) (11 13601.9683257919 7941.4309954751 0.0))
((0 . "LINE") (100 . "AcDbEntity") (8 . "SOLAR") (62 . 7) (370 . 13) (100 . "AcDbLine") (10 13601.9683257919
7941.4309954751 0.0) (11 13844.723280543 7941.4309954751 0.0))
((0 . "LINE") (100 . "AcDbEntity") (8 . "SOLAR") (62 . 7) (370 . 13) (100 . "AcDbLine") (10 14072.3981900452
8212.6696832579 0.0) (11 14966.0633484163 8212.6696832579 0.0))
((0 . "LINE") (100 . "AcDbEntity") (8 . "SOLAR") (62 . 7) (370 . 13) (100 . "AcDbLine") (10 14966.0633484163
8212.6696832579 0.0) (11 14751.1312217195 7873.3031674208 0.0))
((0 . "LINE") (100 . "AcDbEntity") (8 . "SOLAR") (62 . 7) (370 . 13) (100 . "AcDbLine") (10 14751.1312217195
7873.3031674208 0.0) (11 13868.778280543 7873.3031674208 0.0))
((0 . "LINE") (100 . "AcDbEntity") (8 . "SOLAR") (62 . 7) (370 . 13) (100 . "AcDbLine") (10 13868.778280543
7873.3031674208 0.0) (11 14072.3981900452 8212.6696832579 0.0))
((0 . "LINE") (100 . "AcDbEntity") (8 . "SOLAR") (62 . 7) (370 . 13) (100 . "AcDbLine") (10 14074.3495475113
8178.7330316742 0.0) (11 14349.5475113122 8178.7330316742 0.0))
((0 . "LINE") (100 . "AcDbEntity") (8 . "SOLAR") (62 . 7) (370 . 13) (100 . "AcDbLine") (10 14349.5475113122
8178.7330316742 0.0) (11 14647.0588235294 8178.7330316742 0.0))
((0 . "LINE") (100 . "AcDbEntity") (8 . "SOLAR") (62 . 7) (370 . 13) (100 . "AcDbLine") (10 14647.0588235294
8178.7330316742 0.0) (11 14922.2567873303 8178.7330316742 0.0))
((0 . "LINE") (100 . "AcDbEntity") (8 . "SOLAR") (62 . 7) (370 . 13) (100 . "AcDbLine") (10 14922.2567873303
8178.7330316742 0.0) (11 14913.8854638009 8165.4977375566 0.0))
((0 . "LINE") (100 . "AcDbEntity") (8 . "SOLAR") (62 . 7) (370 . 13) (100 . "AcDbLine") (10 14913.8854638009
8165.4977375566 0.0) (11 14874.1216742081 8102.6300904977 0.0))
((0 . "LINE") (100 . "AcDbEntity") (8 . "SOLAR") (62 . 7) (370 . 13) (100 . "AcDbLine") (10 14874.1216742081
8102.6300904977 0.0) (11 14849.6516515837 8063.9423076923 0.0))
((0 . "LINE") (100 . "AcDbEntity") (8 . "SOLAR") (62 . 7) (370 . 13) (100 . "AcDbLine") (10 14849.6516515837
8063.9423076923 0.0) (11 14816.0053733032 8010.7466063348 0.0))
((0 . "LINE") (100 . "AcDbEntity") (8 . "SOLAR") (62 . 7) (370 . 13) (100 . "AcDbLine") (10 14816.0053733032
8010.7466063348 0.0) (11 14793.5745135747 7975.2828054299 0.0))
((0 . "LINE") (100 . "AcDbEntity") (8 . "SOLAR") (62 . 7) (370 . 13) (100 . "AcDbLine") (10 14793.5745135747
7975.2828054299 0.0) (11 14772.1632466063 7941.4309954751 0.0))
((0 . "LINE") (100 . "AcDbEntity") (8 . "SOLAR") (62 . 7) (370 . 13) (100 . "AcDbLine") (10 14772.1632466063
7941.4309954751 0.0) (11 14750.5373303167 7907.2398190045 0.0))
((0 . "LINE") (100 . "AcDbEntity") (8 . "SOLAR") (62 . 7) (370 . 13) (100 . "AcDbLine") (10 14750.5373303167
7907.2398190045 0.0) (11 14478.1297171946 7907.2398190045 0.0))
((0 . "LINE") (100 . "AcDbEntity") (8 . "SOLAR") (62 . 7) (370 . 13) (100 . "AcDbLine") (10 14478.1297171946
7907.2398190045 0.0) (11 14183.6349886878 7907.2398190045 0.0))
((0 . "LINE") (100 . "AcDbEntity") (8 . "SOLAR") (62 . 7) (370 . 13) (100 . "AcDbLine") (10 14183.6349886878
7907.2398190045 0.0) (11 13911.2273755656 7907.2398190045 0.0))
((0 . "LINE") (100 . "AcDbEntity") (8 . "SOLAR") (62 . 7) (370 . 13) (100 . "AcDbLine") (10 13911.2273755656
7907.2398190045 0.0) (11 13931.7705769231 7941.4309954751 0.0))
((0 . "LINE") (100 . "AcDbEntity") (8 . "SOLAR") (62 . 7) (370 . 13) (100 . "AcDbLine") (10 13931.7705769231
7941.4309954751 0.0) (11 13952.1098755656 7975.2828054299 0.0))
((0 . "LINE") (100 . "AcDbEntity") (8 . "SOLAR") (62 . 7) (370 . 13) (100 . "AcDbLine") (10 13952.1098755656
7975.2828054299 0.0) (11 13973.4177036199 8010.7466063348 0.0))
((0 . "LINE") (100 . "AcDbEntity") (8 . "SOLAR") (62 . 7) (370 . 13) (100 . "AcDbLine") (10 13973.4177036199
8010.7466063348 0.0) (11 14005.3794570136 8063.9423076923 0.0))
((0 . "LINE") (100 . "AcDbEntity") (8 . "SOLAR") (62 . 7) (370 . 13) (100 . "AcDbLine") (10 14005.3794570136
8063.9423076923 0.0) (11 14028.6243665158 8102.6300904977 0.0))
((0 . "LINE") (100 . "AcDbEntity") (8 . "SOLAR") (62 . 7) (370 . 13) (100 . "AcDbLine") (10 14028.6243665158
8102.6300904977 0.0) (11 14066.397341629 8165.4977375566 0.0))
((0 . "LINE") (100 . "AcDbEntity") (8 . "SOLAR") (62 . 7) (370 . 13) (100 . "AcDbLine") (10 14066.397341629
8165.4977375566 0.0) (11 14074.3495475113 8178.7330316742 0.0))
((0 . "LINE") (100 . "AcDbEntity") (8 . "SOLAR") (62 . 7) (370 . 13) (100 . "AcDbLine") (10 14349.5475113122
8178.7330316742 0.0) (11 14341.4592760181 8165.4977375566 0.0))
((0 . "LINE") (100 . "AcDbEntity") (8 . "SOLAR") (62 . 7) (370 . 13) (100 . "AcDbLine") (10 14341.4592760181
8165.4977375566 0.0) (11 14303.040158371 8102.6300904977 0.0))
((0 . "LINE") (100 . "AcDbEntity") (8 . "SOLAR") (62 . 7) (370 . 13) (100 . "AcDbLine") (10 14303.040158371
8102.6300904977 0.0) (11 14279.3976244344 8063.9423076923 0.0))
((0 . "LINE") (100 . "AcDbEntity") (8 . "SOLAR") (62 . 7) (370 . 13) (100 . "AcDbLine") (10 14279.3976244344
8063.9423076923 0.0) (11 14246.8891402715 8010.7466063348 0.0))
((0 . "LINE") (100 . "AcDbEntity") (8 . "SOLAR") (62 . 7) (370 . 13) (100 . "AcDbLine") (10 14246.8891402715
8010.7466063348 0.0) (11 14225.216821267 7975.2828054299 0.0))
((0 . "LINE") (100 . "AcDbEntity") (8 . "SOLAR") (62 . 7) (370 . 13) (100 . "AcDbLine") (10 14225.216821267
7975.2828054299 0.0) (11 14204.5296040724 7941.4309954751 0.0))
((0 . "LINE") (100 . "AcDbEntity") (8 . "SOLAR") (62 . 7) (370 . 13) (100 . "AcDbLine") (10 14204.5296040724
7941.4309954751 0.0) (11 14183.6349886878 7907.2398190045 0.0))
((0 . "LINE") (100 . "AcDbEntity") (8 . "SOLAR") (62 . 7) (370 . 13) (100 . "AcDbLine") (10 14647.0588235294
8178.7330316742 0.0) (11 14638.8235294118 8165.4977375566 0.0))
((0 . "LINE") (100 . "AcDbEntity") (8 . "SOLAR") (62 . 7) (370 . 13) (100 . "AcDbLine") (10 14638.8235294118
8165.4977375566 0.0) (11 14599.7058823529 8102.6300904977 0.0))
((0 . "LINE") (100 . "AcDbEntity") (8 . "SOLAR") (62 . 7) (370 . 13) (100 . "AcDbLine") (10 14599.7058823529
8102.6300904977 0.0) (11 14575.6334841629 8063.9423076923 0.0))
((0 . "LINE") (100 . "AcDbEntity") (8 . "SOLAR") (62 . 7) (370 . 13) (100 . "AcDbLine") (10 14575.6334841629
8063.9423076923 0.0) (11 14542.5339366516 8010.7466063348 0.0))
((0 . "LINE") (100 . "AcDbEntity") (8 . "SOLAR") (62 . 7) (370 . 13) (100 . "AcDbLine") (10 14542.5339366516
8010.7466063348 0.0) (11 14520.4675678733 7975.2828054299 0.0))
((0 . "LINE") (100 . "AcDbEntity") (8 . "SOLAR") (62 . 7) (370 . 13) (100 . "AcDbLine") (10 14520.4675678733
7975.2828054299 0.0) (11 14499.404219457 7941.4309954751 0.0))
((0 . "LINE") (100 . "AcDbEntity") (8 . "SOLAR") (62 . 7) (370 . 13) (100 . "AcDbLine") (10 14499.404219457
7941.4309954751 0.0) (11 14478.1297171946 7907.2398190045 0.0))
((0 . "LINE") (100 . "AcDbEntity") (8 . "SOLAR") (62 . 7) (370 . 13) (100 . "AcDbLine") (10 14066.397341629
8165.4977375566 0.0) (11 14341.4592760181 8165.4977375566 0.0))
((0 . "LINE") (100 . "AcDbEntity") (8 . "SOLAR") (62 . 7) (370 . 13) (100 . "AcDbLine") (10 14341.4592760181
8165.4977375566 0.0) (11 14638.8235294118 8165.4977375566 0.0))
((0 . "LINE") (100 . "AcDbEntity") (8 . "SOLAR") (62 . 7) (370 . 13) (100 . "AcDbLine") (10 14638.8235294118
8165.4977375566 0.0) (11 14913.8854638009 8165.4977375566 0.0))
((0 . "LINE") (100 . "AcDbEntity") (8 . "SOLAR") (62 . 7) (370 . 13) (100 . "AcDbLine") (10 14028.6243665158
8102.6300904977 0.0) (11 14303.040158371 8102.6300904977 0.0))
((0 . "LINE") (100 . "AcDbEntity") (8 . "SOLAR") (62 . 7) (370 . 13) (100 . "AcDbLine") (10 14303.040158371
8102.6300904977 0.0) (11 14599.7058823529 8102.6300904977 0.0))
((0 . "LINE") (100 . "AcDbEntity") (8 . "SOLAR") (62 . 7) (370 . 13) (100 . "AcDbLine") (10 14599.7058823529
8102.6300904977 0.0) (11 14874.1216742081 8102.6300904977 0.0))
((0 . "LINE") (100 . "AcDbEntity") (8 . "SOLAR") (62 . 7) (370 . 13) (100 . "AcDbLine") (10 14005.3794570136
8063.9423076923 0.0) (11 14279.3976244344 8063.9423076923 0.0))
((0 . "LINE") (100 . "AcDbEntity") (8 . "SOLAR") (62 . 7) (370 . 13) (100 . "AcDbLine") (10 14279.3976244344
8063.9423076923 0.0) (11 14575.6334841629 8063.9423076923 0.0))
((0 . "LINE") (100 . "AcDbEntity") (8 . "SOLAR") (62 . 7) (370 . 13) (100 . "AcDbLine") (10 14575.6334841629
8063.9423076923 0.0) (11 14849.6516515837 8063.9423076923 0.0))
((0 . "LINE") (100 . "AcDbEntity") (8 . "SOLAR") (62 . 7) (370 . 13) (100 . "AcDbLine") (10 13973.4177036199
8010.7466063348 0.0) (11 14246.8891402715 8010.7466063348 0.0))
((0 . "LINE") (100 . "AcDbEntity") (8 . "SOLAR") (62 . 7) (370 . 13) (100 . "AcDbLine") (10 14246.8891402715
8010.7466063348 0.0) (11 14542.5339366516 8010.7466063348 0.0))
((0 . "LINE") (100 . "AcDbEntity") (8 . "SOLAR") (62 . 7) (370 . 13) (100 . "AcDbLine") (10 14542.5339366516
8010.7466063348 0.0) (11 14816.0053733032 8010.7466063348 0.0))
((0 . "LINE") (100 . "AcDbEntity") (8 . "SOLAR") (62 . 7) (370 . 13) (100 . "AcDbLine") (10 13952.1098755656
7975.2828054299 0.0) (11 14225.216821267 7975.2828054299 0.0))
((0 . "LINE") (100 . "AcDbEntity") (8 . "SOLAR") (62 . 7) (370 . 13) (100 . "AcDbLine") (10 14225.216821267
7975.2828054299 0.0) (11 14520.4675678733 7975.2828054299 0.0))
((0 . "LINE") (100 . "AcDbEntity") (8 . "SOLAR") (62 . 7) (370 . 13) (100 . "AcDbLine") (10 14520.4675678733
7975.2828054299 0.0) (11 14793.5745135747 7975.2828054299 0.0))
((0 . "LINE") (100 . "AcDbEntity") (8 . "SOLAR") (62 . 7) (370 . 13) (100 . "AcDbLine") (10 13931.7705769231
7941.4309954751 0.0) (11 14204.5296040724 7941.4309954751 0.0))
((0 . "LINE") (100 . "AcDbEntity") (8 . "SOLAR") (62 . 7) (370 . 13) (100 . "AcDbLine") (10 14204.5296040724
7941.4309954751 0.0) (11 14499.404219457 7941.4309954751 0.0))
((0 . "LINE") (100 . "AcDbEntity") (8 . "SOLAR") (62 . 7) (370 . 13) (100 . "AcDbLine") (10 14499.404219457
7941.4309954751 0.0) (11 14772.1632466063 7941.4309954751 0.0))
((0 . "LINE") (100 . "AcDbEntity") (8 . "SOLAR") (62 . 7) (370 . 13) (100 . "AcDbLine") (10 15011.3122171946
8212.6696832579 0.0) (11 15848.4162895928 8212.6696832579 0.0))
((0 . "LINE") (100 . "AcDbEntity") (8 . "SOLAR") (62 . 7) (370 . 13) (100 . "AcDbLine") (10 15848.4162895928
8212.6696832579 0.0) (11 15633.4841628959 7873.3031674208 0.0))
((0 . "LINE") (100 . "AcDbEntity") (8 . "SOLAR") (62 . 7) (370 . 13) (100 . "AcDbLine") (10 15633.4841628959
7873.3031674208 0.0) (11 14796.3800904977 7873.3031674208 0.0))
((0 . "LINE") (100 . "AcDbEntity") (8 . "SOLAR") (62 . 7) (370 . 13) (100 . "AcDbLine") (10 14796.3800904977
7873.3031674208 0.0) (11 15011.3122171946 8212.6696832579 0.0))
((0 . "LINE") (100 . "AcDbEntity") (8 . "SOLAR") (62 . 7) (370 . 13) (100 . "AcDbLine") (10 15010.7466063348
8178.7330316742 0.0) (11 15268.853699095 8178.7330316742 0.0))
((0 . "LINE") (100 . "AcDbEntity") (8 . "SOLAR") (62 . 7) (370 . 13) (100 . "AcDbLine") (10 15268.853699095
8178.7330316742 0.0) (11 15547.8883823529 8178.7330316742 0.0))
((0 . "LINE") (100 . "AcDbEntity") (8 . "SOLAR") (62 . 7) (370 . 13) (100 . "AcDbLine") (10 15547.8883823529
8178.7330316742 0.0) (11 15805.9954751131 8178.7330316742 0.0))
((0 . "LINE") (100 . "AcDbEntity") (8 . "SOLAR") (62 . 7) (370 . 13) (100 . "AcDbLine") (10 15805.9954751131
8178.7330316742 0.0) (11 15797.6131221719 8165.4977375566 0.0))
((0 . "LINE") (100 . "AcDbEntity") (8 . "SOLAR") (62 . 7) (370 . 13) (100 . "AcDbLine") (10 15797.6131221719
8165.4977375566 0.0) (11 15760.8597285068 8107.4660633484 0.0))
((0 . "LINE") (100 . "AcDbEntity") (8 . "SOLAR") (62 . 7) (370 . 13) (100 . "AcDbLine") (10 15760.8597285068
8107.4660633484 0.0) (11 15733.2946832579 8063.9423076923 0.0))
((0 . "LINE") (100 . "AcDbEntity") (8 . "SOLAR") (62 . 7) (370 . 13) (100 . "AcDbLine") (10 15733.2946832579
8063.9423076923 0.0) (11 15698.5831447964 8009.1346153846 0.0))
((0 . "LINE") (100 . "AcDbEntity") (8 . "SOLAR") (62 . 7) (370 . 13) (100 . "AcDbLine") (10 15698.5831447964
8009.1346153846 0.0) (11 15677.1436651584 7975.2828054299 0.0))
((0 . "LINE") (100 . "AcDbEntity") (8 . "SOLAR") (62 . 7) (370 . 13) (100 . "AcDbLine") (10 15677.1436651584
7975.2828054299 0.0) (11 15655.7041855204 7941.4309954751 0.0))
((0 . "LINE") (100 . "AcDbEntity") (8 . "SOLAR") (62 . 7) (370 . 13) (100 . "AcDbLine") (10 15655.7041855204
7941.4309954751 0.0) (11 15634.0497737557 7907.2398190045 0.0))
((0 . "LINE") (100 . "AcDbEntity") (8 . "SOLAR") (62 . 7) (370 . 13) (100 . "AcDbLine") (10 15634.0497737557
7907.2398190045 0.0) (11 15375.9426809955 7907.2398190045 0.0))
((0 . "LINE") (100 . "AcDbEntity") (8 . "SOLAR") (62 . 7) (370 . 13) (100 . "AcDbLine") (10 15375.9426809955
7907.2398190045 0.0) (11 15096.9079977376 7907.2398190045 0.0))
((0 . "LINE") (100 . "AcDbEntity") (8 . "SOLAR") (62 . 7) (370 . 13) (100 . "AcDbLine") (10 15096.9079977376
7907.2398190045 0.0) (11 14838.8009049774 7907.2398190045 0.0))
((0 . "LINE") (100 . "AcDbEntity") (8 . "SOLAR") (62 . 7) (370 . 13) (100 . "AcDbLine") (10 14838.8009049774
7907.2398190045 0.0) (11 14860.4553167421 7941.4309954751 0.0))
((0 . "LINE") (100 . "AcDbEntity") (8 . "SOLAR") (62 . 7) (370 . 13) (100 . "AcDbLine") (10 14860.4553167421
7941.4309954751 0.0) (11 14881.8947963801 7975.2828054299 0.0))
((0 . "LINE") (100 . "AcDbEntity") (8 . "SOLAR") (62 . 7) (370 . 13) (100 . "AcDbLine") (10 14881.8947963801
7975.2828054299 0.0) (11 14903.3342760181 8009.1346153846 0.0))
((0 . "LINE") (100 . "AcDbEntity") (8 . "SOLAR") (62 . 7) (370 . 13) (100 . "AcDbLine") (10 14903.3342760181
8009.1346153846 0.0) (11 14938.0458144796 8063.9423076923 0.0))
((0 . "LINE") (100 . "AcDbEntity") (8 . "SOLAR") (62 . 7) (370 . 13) (100 . "AcDbLine") (10 14938.0458144796
8063.9423076923 0.0) (11 14965.6108597285 8107.4660633484 0.0))
((0 . "LINE") (100 . "AcDbEntity") (8 . "SOLAR") (62 . 7) (370 . 13) (100 . "AcDbLine") (10 14965.6108597285
8107.4660633484 0.0) (11 15002.3642533937 8165.4977375566 0.0))
((0 . "LINE") (100 . "AcDbEntity") (8 . "SOLAR") (62 . 7) (370 . 13) (100 . "AcDbLine") (10 15002.3642533937
8165.4977375566 0.0) (11 15010.7466063348 8178.7330316742 0.0))
((0 . "LINE") (100 . "AcDbEntity") (8 . "SOLAR") (62 . 7) (370 . 13) (100 . "AcDbLine") (10 15268.853699095
8178.7330316742 0.0) (11 15260.4713461538 8165.4977375566 0.0))
((0 . "LINE") (100 . "AcDbEntity") (8 . "SOLAR") (62 . 7) (370 . 13) (100 . "AcDbLine") (10 15260.4713461538
8165.4977375566 0.0) (11 15223.7179524887 8107.4660633484 0.0))
((0 . "LINE") (100 . "AcDbEntity") (8 . "SOLAR") (62 . 7) (370 . 13) (100 . "AcDbLine") (10 15223.7179524887
8107.4660633484 0.0) (11 15196.1529072398 8063.9423076923 0.0))
((0 . "LINE") (100 . "AcDbEntity") (8 . "SOLAR") (62 . 7) (370 . 13) (100 . "AcDbLine") (10 15196.1529072398
8063.9423076923 0.0) (11 15161.4413687783 8009.1346153846 0.0))
((0 . "LINE") (100 . "AcDbEntity") (8 . "SOLAR") (62 . 7) (370 . 13) (100 . "AcDbLine") (10 15161.4413687783
8009.1346153846 0.0) (11 15140.0018891403 7975.2828054299 0.0))
((0 . "LINE") (100 . "AcDbEntity") (8 . "SOLAR") (62 . 7) (370 . 13) (100 . "AcDbLine") (10 15140.0018891403
7975.2828054299 0.0) (11 15118.5624095023 7941.4309954751 0.0))
((0 . "LINE") (100 . "AcDbEntity") (8 . "SOLAR") (62 . 7) (370 . 13) (100 . "AcDbLine") (10 15118.5624095023
7941.4309954751 0.0) (11 15096.9079977376 7907.2398190045 0.0))
((0 . "LINE") (100 . "AcDbEntity") (8 . "SOLAR") (62 . 7) (370 . 13) (100 . "AcDbLine") (10 15547.8883823529
8178.7330316742 0.0) (11 15539.5060294118 8165.4977375566 0.0))
((0 . "LINE") (100 . "AcDbEntity") (8 . "SOLAR") (62 . 7) (370 . 13) (100 . "AcDbLine") (10 15539.5060294118
8165.4977375566 0.0) (11 15502.7526357466 8107.4660633484 0.0))
((0 . "LINE") (100 . "AcDbEntity") (8 . "SOLAR") (62 . 7) (370 . 13) (100 . "AcDbLine") (10 15502.7526357466
8107.4660633484 0.0) (11 15475.1875904977 8063.9423076923 0.0))
((0 . "LINE") (100 . "AcDbEntity") (8 . "SOLAR") (62 . 7) (370 . 13) (100 . "AcDbLine") (10 15475.1875904977
8063.9423076923 0.0) (11 15440.4760520362 8009.1346153846 0.0))
((0 . "LINE") (100 . "AcDbEntity") (8 . "SOLAR") (62 . 7) (370 . 13) (100 . "AcDbLine") (10 15440.4760520362
8009.1346153846 0.0) (11 15419.0365723982 7975.2828054299 0.0))
((0 . "LINE") (100 . "AcDbEntity") (8 . "SOLAR") (62 . 7) (370 . 13) (100 . "AcDbLine") (10 15419.0365723982
7975.2828054299 0.0) (11 15397.5970927602 7941.4309954751 0.0))
((0 . "LINE") (100 . "AcDbEntity") (8 . "SOLAR") (62 . 7) (370 . 13) (100 . "AcDbLine") (10 15397.5970927602
7941.4309954751 0.0) (11 15375.9426809955 7907.2398190045 0.0))
((0 . "LINE") (100 . "AcDbEntity") (8 . "SOLAR") (62 . 7) (370 . 13) (100 . "AcDbLine") (10 15002.3642533937
8165.4977375566 0.0) (11 15260.4713461538 8165.4977375566 0.0))
((0 . "LINE") (100 . "AcDbEntity") (8 . "SOLAR") (62 . 7) (370 . 13) (100 . "AcDbLine") (10 15260.4713461538
8165.4977375566 0.0) (11 15539.5060294118 8165.4977375566 0.0))
((0 . "LINE") (100 . "AcDbEntity") (8 . "SOLAR") (62 . 7) (370 . 13) (100 . "AcDbLine") (10 15539.5060294118
8165.4977375566 0.0) (11 15797.6131221719 8165.4977375566 0.0))
((0 . "LINE") (100 . "AcDbEntity") (8 . "SOLAR") (62 . 7) (370 . 13) (100 . "AcDbLine") (10 14965.6108597285
8107.4660633484 0.0) (11 15223.7179524887 8107.4660633484 0.0))
((0 . "LINE") (100 . "AcDbEntity") (8 . "SOLAR") (62 . 7) (370 . 13) (100 . "AcDbLine") (10 15223.7179524887
8107.4660633484 0.0) (11 15502.7526357466 8107.4660633484 0.0))
((0 . "LINE") (100 . "AcDbEntity") (8 . "SOLAR") (62 . 7) (370 . 13) (100 . "AcDbLine") (10 15502.7526357466
8107.4660633484 0.0) (11 15760.8597285068 8107.4660633484 0.0))
((0 . "LINE") (100 . "AcDbEntity") (8 . "SOLAR") (62 . 7) (370 . 13) (100 . "AcDbLine") (10 14938.0458144796
8063.9423076923 0.0) (11 15196.1529072398 8063.9423076923 0.0))
((0 . "LINE") (100 . "AcDbEntity") (8 . "SOLAR") (62 . 7) (370 . 13) (100 . "AcDbLine") (10 15196.1529072398
8063.9423076923 0.0) (11 15475.1875904977 8063.9423076923 0.0))
((0 . "LINE") (100 . "AcDbEntity") (8 . "SOLAR") (62 . 7) (370 . 13) (100 . "AcDbLine") (10 15475.1875904977
8063.9423076923 0.0) (11 15733.2946832579 8063.9423076923 0.0))
((0 . "LINE") (100 . "AcDbEntity") (8 . "SOLAR") (62 . 7) (370 . 13) (100 . "AcDbLine") (10 14903.3342760181
8009.1346153846 0.0) (11 15161.4413687783 8009.1346153846 0.0))
((0 . "LINE") (100 . "AcDbEntity") (8 . "SOLAR") (62 . 7) (370 . 13) (100 . "AcDbLine") (10 15161.4413687783
8009.1346153846 0.0) (11 15440.4760520362 8009.1346153846 0.0))
((0 . "LINE") (100 . "AcDbEntity") (8 . "SOLAR") (62 . 7) (370 . 13) (100 . "AcDbLine") (10 15440.4760520362
8009.1346153846 0.0) (11 15698.5831447964 8009.1346153846 0.0))
((0 . "LINE") (100 . "AcDbEntity") (8 . "SOLAR") (62 . 7) (370 . 13) (100 . "AcDbLine") (10 14881.8947963801
7975.2828054299 0.0) (11 15140.0018891403 7975.2828054299 0.0))
((0 . "LINE") (100 . "AcDbEntity") (8 . "SOLAR") (62 . 7) (370 . 13) (100 . "AcDbLine") (10 15140.0018891403
7975.2828054299 0.0) (11 15419.0365723982 7975.2828054299 0.0))
((0 . "LINE") (100 . "AcDbEntity") (8 . "SOLAR") (62 . 7) (370 . 13) (100 . "AcDbLine") (10 15419.0365723982
7975.2828054299 0.0) (11 15677.1436651584 7975.2828054299 0.0))
((0 . "LINE") (100 . "AcDbEntity") (8 . "SOLAR") (62 . 7) (370 . 13) (100 . "AcDbLine") (10 14860.4553167421
7941.4309954751 0.0) (11 15118.5624095023 7941.4309954751 0.0))
((0 . "LINE") (100 . "AcDbEntity") (8 . "SOLAR") (62 . 7) (370 . 13) (100 . "AcDbLine") (10 15118.5624095023
7941.4309954751 0.0) (11 15397.5970927602 7941.4309954751 0.0))
((0 . "LINE") (100 . "AcDbEntity") (8 . "SOLAR") (62 . 7) (370 . 13) (100 . "AcDbLine") (10 15397.5970927602
7941.4309954751 0.0) (11 15655.7041855204 7941.4309954751 0.0))
((0 . "LINE") (100 . "AcDbEntity") (8 . "MASONRY") (62 . 7) (370 . 13) (100 . "AcDbLine") (10 2801.6586651584
220.5882352941 0.0) (11 2801.6586651584 226.2015384615 0.0))
((0 . "LINE") (100 . "AcDbEntity") (8 . "MASONRY") (62 . 7) (370 . 13) (100 . "AcDbLine") (10 2797.8871153846
348.7758710407 0.0) (11 2797.8871153846 765.4609502262 0.0))
((0 . "LINE") (100 . "AcDbEntity") (8 . "MASONRY") (62 . 7) (370 . 13) (100 . "AcDbLine") (10 2794.1176470588
3580.3167420814 0.0) (11 2794.1176470588 3012.8202828054 0.0))
((0 . "LINE") (100 . "AcDbEntity") (8 . "MASONRY") (62 . 7) (370 . 13) (100 . "AcDbLine") (10 2794.1176470588
2812.9715723982 0.0) (11 2794.1176470588 2417.0439705882 0.0))
((0 . "LINE") (100 . "AcDbEntity") (8 . "MASONRY") (62 . 7) (370 . 13) (100 . "AcDbLine") (10 2794.1176470588
2417.0439705882 0.0) (11 2794.1176470588 2398.1900452489 0.0))
((0 . "LINE") (100 . "AcDbEntity") (8 . "MASONRY") (62 . 7) (370 . 13) (100 . "AcDbLine") (10 2794.1176470588
2812.9715723982 0.0) (11 2794.1176470588 3012.8202828054 0.0))
((0 . "LINE") (100 . "AcDbEntity") (8 . "MASONRY") (62 . 7) (370 . 13) (100 . "AcDbLine") (10 2794.1176470588
1259.4259276018 0.0) (11 2794.1176470588 1293.3625791855 0.0))
((0 . "LINE") (100 . "AcDbEntity") (8 . "MASONRY") (62 . 7) (370 . 13) (100 . "AcDbLine") (10 2794.1176470588
1259.4259276018 0.0) (11 2794.1176470588 1180.2404072398 0.0))
((0 . "LINE") (100 . "AcDbEntity") (8 . "MASONRY") (62 . 7) (370 . 13) (100 . "AcDbLine") (10 2794.1176470588
1180.2404072398 0.0) (11 2794.1176470588 1150.0763348416 0.0))
((0 . "LINE") (100 . "AcDbEntity") (8 . "MASONRY") (62 . 7) (370 . 13) (100 . "AcDbLine") (10 2846.9082239819
1866.5158371041 0.0) (11 2869.532658371 1866.5158371041 0.0))
((0 . "LINE") (100 . "AcDbEntity") (8 . "MASONRY") (62 . 7) (370 . 13) (100 . "AcDbLine") (10 2901.5837104072
1168.9295701357 0.0) (11 2846.9082239819 1168.9295701357 0.0))
((0 . "LINE") (100 . "AcDbEntity") (8 . "MASONRY") (62 . 7) (370 . 13) (100 . "AcDbLine") (10 2850.6787330317
3470.9650791855 0.0) (11 3016.5911312217 3470.9650791855 0.0))
((0 . "LINE") (100 . "AcDbEntity") (8 . "MASONRY") (62 . 7) (370 . 13) (100 . "AcDbLine") (10 2933.6351131222
3355.9579977376 0.0) (11 2850.6787330317 3355.9579977376 0.0))
((0 . "LINE") (100 . "AcDbEntity") (8 . "MASONRY") (62 . 7) (370 . 13) (100 . "AcDbLine") (10 2899.6984615385
2754.5248868778 0.0) (11 2850.6787330317 2754.5248868778 0.0))
((0 . "LINE") (100 . "AcDbEntity") (8 . "MASONRY") (62 . 7) (370 . 13) (100 . "AcDbLine") (10 2850.6787330317
2677.2249660633 0.0) (11 2850.6787330317 2684.7659841629 0.0))
((0 . "LINE") (100 . "AcDbEntity") (8 . "MASONRY") (62 . 7) (370 . 13) (100 . "AcDbLine") (10 2850.6787330317
2669.6832579186 0.0) (11 2850.6787330317 2677.2249660633 0.0))
((0 . "LINE") (100 . "AcDbEntity") (8 . "MASONRY") (62 . 7) (370 . 13) (100 . "AcDbLine") (10 2850.6787330317
2501.8855995475 0.0) (11 3344.6454298643 2501.8855995475 0.0))
((0 . "LINE") (100 . "AcDbEntity") (8 . "MASONRY") (62 . 7) (370 . 13) (100 . "AcDbLine") (10 2850.6787330317
2378.1319909502 0.0) (11 2918.5520361991 2378.1319909502 0.0))
((0 . "LINE") (100 . "AcDbEntity") (8 . "MASONRY") (62 . 7) (370 . 13) (100 . "AcDbLine") (10 2918.5520361991
2378.1319909502 0.0) (11 2933.6351131222 2378.1319909502 0.0))
((0 . "LINE") (100 . "AcDbEntity") (8 . "MASONRY") (62 . 7) (370 . 13) (100 . "AcDbLine") (10 2922.4775452489
2279.4117647059 0.0) (11 2850.6787330317 2279.4117647059 0.0))
((0 . "LINE") (100 . "AcDbEntity") (8 . "MASONRY") (62 . 7) (370 . 13) (100 . "AcDbLine") (10 2911.010678733
2230.3916968326 0.0) (11 2850.6787330317 2230.3916968326 0.0))
((0 . "LINE") (100 . "AcDbEntity") (8 . "MASONRY") (62 . 7) (370 . 13) (100 . "AcDbLine") (10 2850.6787330317
1966.4367420814 0.0) (11 3084.4644343891 1966.4367420814 0.0))
((0 . "LINE") (100 . "AcDbEntity") (8 . "MASONRY") (62 . 7) (370 . 13) (100 . "AcDbLine") (10 3084.4644343891
1966.4367420814 0.0) (11 3159.8794570136 1966.4367420814 0.0))
((0 . "LINE") (100 . "AcDbEntity") (8 . "MASONRY") (62 . 7) (370 . 13) (100 . "AcDbLine") (10 3159.8794570136
1966.4367420814 0.0) (11 3574.6606334842 1966.4367420814 0.0))
((0 . "LINE") (100 . "AcDbEntity") (8 . "MASONRY") (62 . 7) (370 . 13) (100 . "AcDbLine") (10 2899.695 1723.2268325792
0.0) (11 2899.695 1734.4624095023 0.0))
((0 . "LINE") (100 . "AcDbEntity") (8 . "MASONRY") (62 . 7) (370 . 13) (100 . "AcDbLine") (10 2899.695 1734.4624095023
0.0) (11 2850.6787330317 1734.4624095023 0.0))
((0 . "LINE") (100 . "AcDbEntity") (8 . "MASONRY") (62 . 7) (370 . 13) (100 . "AcDbLine") (10 3141.025520362
1670.4383257919 0.0) (11 2850.6787330317 1670.4383257919 0.0))
((0 . "LINE") (100 . "AcDbEntity") (8 . "MASONRY") (62 . 7) (370 . 13) (100 . "AcDbLine") (10 2850.6787330317
1457.3911085973 0.0) (11 3027.9033484163 1457.3911085973 0.0))
((0 . "LINE") (100 . "AcDbEntity") (8 . "MASONRY") (62 . 7) (370 . 13) (100 . "AcDbLine") (10 2892.1567420814
1395.1739140271 0.0) (11 2850.6787330317 1395.1739140271 0.0))
((0 . "LINE") (100 . "AcDbEntity") (8 . "MASONRY") (62 . 7) (370 . 13) (100 . "AcDbLine") (10 2854.4492420814
3263.500780543 0.0) (11 3178.7330316742 3263.500780543 0.0))
((0 . "LINE") (100 . "AcDbEntity") (8 . "MASONRY") (62 . 7) (370 . 13) (100 . "AcDbLine") (10 3178.7330316742
3263.500780543 0.0) (11 3229.6380090498 3263.500780543 0.0))
((0 . "LINE") (100 . "AcDbEntity") (8 . "MASONRY") (62 . 7) (370 . 13) (100 . "AcDbLine") (10 2961.9153054299
3190.0452488688 0.0) (11 2854.4492420814 3190.0452488688 0.0))
((0 . "LINE") (100 . "AcDbEntity") (8 . "MASONRY") (62 . 7) (370 . 13) (100 . "AcDbLine") (10 2895.92760181
2677.2249660633 0.0) (11 2850.6787330317 2677.2249660633 0.0))
((0 . "LINE") (100 . "AcDbEntity") (8 . "MASONRY") (62 . 7) (370 . 13) (100 . "AcDbLine") (10 2899.620780543
2643.2883144796 0.0) (11 2899.620780543 2625.036459276 0.0))
((0 . "LINE") (100 . "AcDbEntity") (8 . "MASONRY") (62 . 7) (370 . 13) (100 . "AcDbLine") (10 2899.620780543
2625.036459276 0.0) (11 2854.4492420814 2625.036459276 0.0))
((0 . "LINE") (100 . "AcDbEntity") (8 . "MASONRY") (62 . 7) (370 . 13) (100 . "AcDbLine") (10 3259.8041515837
2576.6191402715 0.0) (11 2954.4481674208 2576.6191402715 0.0))
((0 . "LINE") (100 . "AcDbEntity") (8 . "MASONRY") (62 . 7) (370 . 13) (100 . "AcDbLine") (10 2954.4481674208
2576.6191402715 0.0) (11 2954.4481674208 2597.9621153846 0.0))
((0 . "LINE") (100 . "AcDbEntity") (8 . "MASONRY") (62 . 7) (370 . 13) (100 . "AcDbLine") (10 2954.4481674208
2597.9621153846 0.0) (11 2854.4492420814 2597.9621153846 0.0))
((0 . "LINE") (100 . "AcDbEntity") (8 . "MASONRY") (62 . 7) (370 . 13) (100 . "AcDbLine") (10 2978.8839819005
1606.334841629 0.0) (11 2854.4492420814 1606.334841629 0.0))
((0 . "LINE") (100 . "AcDbEntity") (8 . "MASONRY") (62 . 7) (370 . 13) (100 . "AcDbLine") (10 2854.4492420814
1027.5268552036 0.0) (11 2924.2081447964 1027.5268552036 0.0))
((0 . "LINE") (100 . "AcDbEntity") (8 . "MASONRY") (62 . 7) (370 . 13) (100 . "AcDbLine") (10 3095.7766515837
984.1628959276 0.0) (11 3095.7766515837 960.2556221719 0.0))
((0 . "LINE") (100 . "AcDbEntity") (8 . "MASONRY") (62 . 7) (370 . 13) (100 . "AcDbLine") (10 3095.7766515837
960.2556221719 0.0) (11 2854.4492420814 960.2556221719 0.0))
((0 . "LINE") (100 . "AcDbEntity") (8 . "MASONRY") (62 . 7) (370 . 13) (100 . "AcDbLine") (10 2854.4492420814
785.5307466063 0.0) (11 2998.3662104072 785.5307466063 0.0))
((0 . "LINE") (100 . "AcDbEntity") (8 . "MASONRY") (62 . 7) (370 . 13) (100 . "AcDbLine") (10 3075.6807352941
780.5298642534 0.0) (11 3182.5038914027 780.5298642534 0.0))
((0 . "LINE") (100 . "AcDbEntity") (8 . "MASONRY") (62 . 7) (370 . 13) (100 . "AcDbLine") (10 2877.0736764706
584.4640950226 0.0) (11 2854.4492420814 584.4640950226 0.0))
((0 . "LINE") (100 . "AcDbEntity") (8 . "MASONRY") (62 . 7) (370 . 13) (100 . "AcDbLine") (10 2858.2204411765
2973.2282126697 0.0) (11 3054.2986425339 2973.2282126697 0.0))
((0 . "LINE") (100 . "AcDbEntity") (8 . "MASONRY") (62 . 7) (370 . 13) (100 . "AcDbLine") (10 3054.2986425339
2899.6981108597 0.0) (11 2858.2204411765 2899.6981108597 0.0))
((0 . "LINE") (100 . "AcDbEntity") (8 . "MASONRY") (62 . 7) (370 . 13) (100 . "AcDbLine") (10 3120.2863461538
2820.5125904977 0.0) (11 2858.2204411765 2820.5125904977 0.0))
((0 . "LINE") (100 . "AcDbEntity") (8 . "MASONRY") (62 . 7) (370 . 13) (100 . "AcDbLine") (10 2941.1764705882
720.212081448 0.0) (11 2858.2204411765 720.212081448 0.0))
((0 . "LINE") (100 . "AcDbEntity") (8 . "MASONRY") (62 . 7) (370 . 13) (100 . "AcDbLine") (10 2857.3035294118
226.0779524887 0.0) (11 2857.3035294118 220.5882352941 0.0))
((0 . "LINE") (100 . "AcDbEntity") (8 . "MASONRY") (62 . 7) (370 . 13) (100 . "AcDbLine") (10 3344.6454298643
3046.7569343891 0.0) (11 2861.9909502262 3046.7569343891 0.0))
((0 . "LINE") (100 . "AcDbEntity") (8 . "MASONRY") (62 . 7) (370 . 13) (100 . "AcDbLine") (10 2905.354219457
1266.9683257919 0.0) (11 2861.9909502262 1266.9683257919 0.0))
((0 . "LINE") (100 . "AcDbEntity") (8 . "MASONRY") (62 . 7) (370 . 13) (100 . "AcDbLine") (10 2897.8132013575
3001.5080656109 0.0) (11 2897.8132013575 2993.9670475113 0.0))
((0 . "LINE") (100 . "AcDbEntity") (8 . "MASONRY") (62 . 7) (370 . 13) (100 . "AcDbLine") (10 2905.354219457
1332.956719457 0.0) (11 2895.92760181 1332.956719457 0.0))
((0 . "LINE") (100 . "AcDbEntity") (8 . "MASONRY") (62 . 7) (370 . 13) (100 . "AcDbLine") (10 2903.4693099548
3525.6412556561 0.0) (11 2903.4693099548 3518.0995475113 0.0))
((0 . "LINE") (100 . "AcDbEntity") (8 . "MASONRY") (62 . 7) (370 . 13) (100 . "AcDbLine") (10 2899.6984615385
2754.5248868778 0.0) (11 2899.6984615385 2703.6199095023 0.0))
((0 . "LINE") (100 . "AcDbEntity") (8 . "MASONRY") (62 . 7) (370 . 13) (100 . "AcDbLine") (10 2899.6984615385
2754.5248868778 0.0) (11 3110.8597285068 2754.5248868778 0.0))
((0 . "LINE") (100 . "AcDbEntity") (8 . "MASONRY") (62 . 7) (370 . 13) (100 . "AcDbLine") (10 3110.8597285068
2754.5248868778 0.0) (11 3220.211040724 2754.5248868778 0.0))
((0 . "LINE") (100 . "AcDbEntity") (8 . "MASONRY") (62 . 7) (370 . 13) (100 . "AcDbLine") (10 2914.7811764706
2058.8235294118 0.0) (11 2899.6984615385 2058.8235294118 0.0))
((0 . "LINE") (100 . "AcDbEntity") (8 . "MASONRY") (62 . 7) (370 . 13) (100 . "AcDbLine") (10 2905.354219457
1225.4892760181 0.0) (11 2905.354219457 1265.0088461538 0.0))
((0 . "LINE") (100 . "AcDbEntity") (8 . "MASONRY") (62 . 7) (370 . 13) (100 . "AcDbLine") (10 2905.354219457
1265.0088461538 0.0) (11 2905.354219457 1266.9683257919 0.0))
((0 . "LINE") (100 . "AcDbEntity") (8 . "MASONRY") (62 . 7) (370 . 13) (100 . "AcDbLine") (10 2901.5837104072
1168.9295701357 0.0) (11 2924.2081447964 1168.9295701357 0.0))
((0 . "LINE") (100 . "AcDbEntity") (8 . "MASONRY") (62 . 7) (370 . 13) (100 . "AcDbLine") (10 2901.5837104072
1168.9295701357 0.0) (11 2901.5837104072 1187.7828054299 0.0))
((0 . "LINE") (100 . "AcDbEntity") (8 . "MASONRY") (62 . 7) (370 . 13) (100 . "AcDbLine") (10 2899.6984615385
588.2352941176 0.0) (11 2918.5520361991 588.2352941176 0.0))
((0 . "LINE") (100 . "AcDbEntity") (8 . "MASONRY") (62 . 7) (370 . 13) (100 . "AcDbLine") (10 3044.8716742081
1376.320678733 0.0) (11 3044.8716742081 1391.3253846154 0.0))
((0 . "LINE") (100 . "AcDbEntity") (8 . "MASONRY") (62 . 7) (370 . 13) (100 . "AcDbLine") (10 3044.8716742081
1391.3253846154 0.0) (11 2903.468959276 1391.3253846154 0.0))
((0 . "LINE") (100 . "AcDbEntity") (8 . "MASONRY") (62 . 7) (370 . 13) (100 . "AcDbLine") (10 2905.354219457
1266.9683257919 0.0) (11 2905.354219457 1332.956719457 0.0))
((0 . "LINE") (100 . "AcDbEntity") (8 . "MASONRY") (62 . 7) (370 . 13) (100 . "AcDbLine") (10 2937.4056108597
1332.956719457 0.0) (11 2905.354219457 1332.956719457 0.0))
((0 . "LINE") (100 . "AcDbEntity") (8 . "MASONRY") (62 . 7) (370 . 13) (100 . "AcDbLine") (10 2905.354219457
1265.0088461538 0.0) (11 3146.681979638 1265.0088461538 0.0))
((0 . "LINE") (100 . "AcDbEntity") (8 . "MASONRY") (62 . 7) (370 . 13) (100 . "AcDbLine") (10 2914.7811764706
2058.8235294118 0.0) (11 2926.0933936652 2058.8235294118 0.0))
((0 . "LINE") (100 . "AcDbEntity") (8 . "MASONRY") (62 . 7) (370 . 13) (100 . "AcDbLine") (10 2914.7811764706
2058.8235294118 0.0) (11 2914.7811764706 2100.3018891403 0.0))
((0 . "LINE") (100 . "AcDbEntity") (8 . "MASONRY") (62 . 7) (370 . 13) (100 . "AcDbLine") (10 3131.5985633484
1858.9741289593 0.0) (11 2911.010678733 1858.9741289593 0.0))
((0 . "LINE") (100 . "AcDbEntity") (8 . "MASONRY") (62 . 7) (370 . 13) (100 . "AcDbLine") (10 2914.7811764706
2115.3846153846 0.0) (11 2914.7811764706 2100.3018891403 0.0))
((0 . "LINE") (100 . "AcDbEntity") (8 . "MASONRY") (62 . 7) (370 . 13) (100 . "AcDbLine") (10 2922.4775452489
2279.4117647059 0.0) (11 2922.4775452489 2265.0788574661 0.0))
((0 . "LINE") (100 . "AcDbEntity") (8 . "MASONRY") (62 . 7) (370 . 13) (100 . "AcDbLine") (10 2922.4775452489
2265.0788574661 0.0) (11 3088.2352941176 2265.0788574661 0.0))
((0 . "LINE") (100 . "AcDbEntity") (8 . "MASONRY") (62 . 7) (370 . 13) (100 . "AcDbLine") (10 3088.2352941176
2265.0788574661 0.0) (11 3088.2352941176 2281.2973642534 0.0))
((0 . "LINE") (100 . "AcDbEntity") (8 . "MASONRY") (62 . 7) (370 . 13) (100 . "AcDbLine") (10 2922.4775452489
2279.4117647059 0.0) (11 2922.4775452489 2318.9299547511 0.0))
((0 . "LINE") (100 . "AcDbEntity") (8 . "MASONRY") (62 . 7) (370 . 13) (100 . "AcDbLine") (10 2922.4775452489
2318.9299547511 0.0) (11 2952.4886877828 2318.9299547511 0.0))
((0 . "LINE") (100 . "AcDbEntity") (8 . "MASONRY") (62 . 7) (370 . 13) (100 . "AcDbLine") (10 3180.6186312217
2156.8629751131 0.0) (11 2918.5520361991 2156.8629751131 0.0))
((0 . "LINE") (100 . "AcDbEntity") (8 . "MASONRY") (62 . 7) (370 . 13) (100 . "AcDbLine") (10 2978.8839819005
2100.3018891403 0.0) (11 2914.7811764706 2100.3018891403 0.0))
((0 . "LINE") (100 . "AcDbEntity") (8 . "MASONRY") (62 . 7) (370 . 13) (100 . "AcDbLine") (10 2924.2081447964
1168.9295701357 0.0) (11 2924.2081447964 1142.5339366516 0.0))
((0 . "LINE") (100 . "AcDbEntity") (8 . "MASONRY") (62 . 7) (370 . 13) (100 . "AcDbLine") (10 2922.3228959276
1093.35989819 0.0) (11 2933.6416628959 1093.35989819 0.0))
((0 . "LINE") (100 . "AcDbEntity") (8 . "MASONRY") (62 . 7) (370 . 13) (100 . "AcDbLine") (10 2933.6416628959
1093.35989819 0.0) (11 2975.1131221719 1093.35989819 0.0))
((0 . "LINE") (100 . "AcDbEntity") (8 . "MASONRY") (62 . 7) (370 . 13) (100 . "AcDbLine") (10 2924.2081447964
1044.493800905 0.0) (11 2924.2081447964 1027.5268552036 0.0))
((0 . "LINE") (100 . "AcDbEntity") (8 . "MASONRY") (62 . 7) (370 . 13) (100 . "AcDbLine") (10 2933.6351131222
3329.5623642534 0.0) (11 2926.0933936652 3329.5623642534 0.0))
((0 . "LINE") (100 . "AcDbEntity") (8 . "MASONRY") (62 . 7) (370 . 13) (100 . "AcDbLine") (10 2924.2081447964
1168.9295701357 0.0) (11 3046.7572850679 1168.9295701357 0.0))
((0 . "LINE") (100 . "AcDbEntity") (8 . "MASONRY") (62 . 7) (370 . 13) (100 . "AcDbLine") (10 2988.310938914
1027.5268552036 0.0) (11 2924.2081447964 1027.5268552036 0.0))
((0 . "LINE") (100 . "AcDbEntity") (8 . "MASONRY") (62 . 7) (370 . 13) (100 . "AcDbLine") (10 2933.6351131222
3355.9579977376 0.0) (11 2933.6351131222 3329.5623642534 0.0))
((0 . "LINE") (100 . "AcDbEntity") (8 . "MASONRY") (62 . 7) (370 . 13) (100 . "AcDbLine") (10 2933.6351131222
3355.9579977376 0.0) (11 2933.6351131222 3413.8758031674 0.0))
((0 . "LINE") (100 . "AcDbEntity") (8 . "MASONRY") (62 . 7) (370 . 13) (100 . "AcDbLine") (10 2933.6351131222
3413.8758031674 0.0) (11 3024.1328506787 3413.8758031674 0.0))
((0 . "LINE") (100 . "AcDbEntity") (8 . "MASONRY") (62 . 7) (370 . 13) (100 . "AcDbLine") (10 2933.6351131222
3329.5623642534 0.0) (11 3229.6380090498 3329.5623642534 0.0))
((0 . "LINE") (100 . "AcDbEntity") (8 . "MASONRY") (62 . 7) (370 . 13) (100 . "AcDbLine") (10 2933.6351131222
2378.1319909502 0.0) (11 3363.4993665158 2378.1319909502 0.0))
((0 . "LINE") (100 . "AcDbEntity") (8 . "MASONRY") (62 . 7) (370 . 13) (100 . "AcDbLine") (10 3363.4993665158
2378.1319909502 0.0) (11 3386.123800905 2378.1319909502 0.0))
((0 . "LINE") (100 . "AcDbEntity") (8 . "MASONRY") (62 . 7) (370 . 13) (100 . "AcDbLine") (10 3386.123800905
2378.1319909502 0.0) (11 3518.0995475113 2378.1319909502 0.0))
((0 . "LINE") (100 . "AcDbEntity") (8 . "MASONRY") (62 . 7) (370 . 13) (100 . "AcDbLine") (10 2933.6351131222
2360.4828846154 0.0) (11 2933.6351131222 2378.1319909502 0.0))
((0 . "LINE") (100 . "AcDbEntity") (8 . "MASONRY") (62 . 7) (370 . 13) (100 . "AcDbLine") (10 3318.2504977376
2643.2848642534 0.0) (11 3235.300678733 2643.2848642534 0.0))
((0 . "LINE") (100 . "AcDbEntity") (8 . "MASONRY") (62 . 7) (370 . 13) (100 . "AcDbLine") (10 3235.300678733
2643.2848642534 0.0) (11 3208.8988235294 2643.2848642534 0.0))
((0 . "LINE") (100 . "AcDbEntity") (8 . "MASONRY") (62 . 7) (370 . 13) (100 . "AcDbLine") (10 3208.8988235294
2643.2848642534 0.0) (11 2937.4056108597 2643.2848642534 0.0))
((0 . "LINE") (100 . "AcDbEntity") (8 . "MASONRY") (62 . 7) (370 . 13) (100 . "AcDbLine") (10 2939.2908710407
1745.8512669683 0.0) (11 2939.2908710407 1757.1634841629 0.0))
((0 . "LINE") (100 . "AcDbEntity") (8 . "MASONRY") (62 . 7) (370 . 13) (100 . "AcDbLine") (10 2937.4056108597
1332.956719457 0.0) (11 2937.4056108597 1342.3840271493 0.0))
((0 . "LINE") (100 . "AcDbEntity") (8 . "MASONRY") (62 . 7) (370 . 13) (100 . "AcDbLine") (10 2937.4056108597
1332.956719457 0.0) (11 3048.6425339367 1332.956719457 0.0))
((0 . "LINE") (100 . "AcDbEntity") (8 . "MASONRY") (62 . 7) (370 . 13) (100 . "AcDbLine") (10 2941.1764705882
1813.8799208145 0.0) (11 3122.1653846154 1813.8799208145 0.0))
((0 . "LINE") (100 . "AcDbEntity") (8 . "MASONRY") (62 . 7) (370 . 13) (100 . "AcDbLine") (10 3122.1653846154
1813.8799208145 0.0) (11 3133.4841628959 1813.8799208145 0.0))
((0 . "LINE") (100 . "AcDbEntity") (8 . "MASONRY") (62 . 7) (370 . 13) (100 . "AcDbLine") (10 2941.1764705882
739.0639366516 0.0) (11 2941.1764705882 720.212081448 0.0))
((0 . "LINE") (100 . "AcDbEntity") (8 . "MASONRY") (62 . 7) (370 . 13) (100 . "AcDbLine") (10 2941.1764705882
720.212081448 0.0) (11 2975.1131221719 720.212081448 0.0))
((0 . "LINE") (100 . "AcDbEntity") (8 . "MASONRY") (62 . 7) (370 . 13) (100 . "AcDbLine") (10 3061.84 842.7891742081
0.0) (11 3008.5681900452 842.7891742081 0.0))
((0 . "LINE") (100 . "AcDbEntity") (8 . "MASONRY") (62 . 7) (370 . 13) (100 . "AcDbLine") (10 2982.7756561086
842.0690497738 0.0) (11 2948.7178280543 842.0690497738 0.0))
((0 . "LINE") (100 . "AcDbEntity") (8 . "MASONRY") (62 . 7) (370 . 13) (100 . "AcDbLine") (10 2952.4886877828
2055.053020362 0.0) (11 3016.5911312217 2055.053020362 0.0))
((0 . "LINE") (100 . "AcDbEntity") (8 . "MASONRY") (62 . 7) (370 . 13) (100 . "AcDbLine") (10 2961.9153054299
3190.0452488688 0.0) (11 2961.9153054299 3174.9625226244 0.0))
((0 . "LINE") (100 . "AcDbEntity") (8 . "MASONRY") (62 . 7) (370 . 13) (100 . "AcDbLine") (10 2961.9153054299
3148.5668891403 0.0) (11 2961.9153054299 3156.1085972851 0.0))
((0 . "LINE") (100 . "AcDbEntity") (8 . "MASONRY") (62 . 7) (370 . 13) (100 . "AcDbLine") (10 2960.0300452489
3107.0885294118 0.0) (11 3280.5429864253 3107.0885294118 0.0))
((0 . "LINE") (100 . "AcDbEntity") (8 . "MASONRY") (62 . 7) (370 . 13) (100 . "AcDbLine") (10 3148.567239819
3190.0452488688 0.0) (11 2961.9153054299 3190.0452488688 0.0))
((0 . "LINE") (100 . "AcDbEntity") (8 . "MASONRY") (62 . 7) (370 . 13) (100 . "AcDbLine") (10 2965.6865045249
535.4440271493 0.0) (11 2965.6865045249 546.7562443439 0.0))
((0 . "LINE") (100 . "AcDbEntity") (8 . "MASONRY") (62 . 7) (370 . 13) (100 . "AcDbLine") (10 2978.8839819005
1632.7290950226 0.0) (11 2978.8839819005 1606.334841629 0.0))
((0 . "LINE") (100 . "AcDbEntity") (8 . "MASONRY") (62 . 7) (370 . 13) (100 . "AcDbLine") (10 3306.938280543
1606.334841629 0.0) (11 2978.8839819005 1606.334841629 0.0))
((0 . "LINE") (100 . "AcDbEntity") (8 . "MASONRY") (62 . 7) (370 . 13) (100 . "AcDbLine") (10 3042.9864253394
2326.5462330317 0.0) (11 2986.4253393665 2326.5462330317 0.0))
((0 . "LINE") (100 . "AcDbEntity") (8 . "MASONRY") (62 . 7) (370 . 13) (100 . "AcDbLine") (10 2986.4253393665
1743.9663574661 0.0) (11 3039.2155656109 1743.9663574661 0.0))
((0 . "LINE") (100 . "AcDbEntity") (8 . "MASONRY") (62 . 7) (370 . 13) (100 . "AcDbLine") (10 2986.4253393665
1099.0940271493 0.0) (11 3567.1192760181 1099.0940271493 0.0))
((0 . "LINE") (100 . "AcDbEntity") (8 . "MASONRY") (62 . 7) (370 . 13) (100 . "AcDbLine") (10 3567.1192760181
1099.0940271493 0.0) (11 3731.1464253394 1099.0940271493 0.0))
((0 . "LINE") (100 . "AcDbEntity") (8 . "MASONRY") (62 . 7) (370 . 13) (100 . "AcDbLine") (10 3054.2986425339
1027.5268552036 0.0) (11 2988.310938914 1027.5268552036 0.0))
((0 . "LINE") (100 . "AcDbEntity") (8 . "MASONRY") (62 . 7) (370 . 13) (100 . "AcDbLine") (10 2988.310938914
1027.5268552036 0.0) (11 2988.310938914 1055.8060180995 0.0))
((0 . "LINE") (100 . "AcDbEntity") (8 . "MASONRY") (62 . 7) (370 . 13) (100 . "AcDbLine") (10 3010.9353733032
588.2352941176 0.0) (11 3010.9353733032 580.6928959276 0.0))
((0 . "LINE") (100 . "AcDbEntity") (8 . "MASONRY") (62 . 7) (370 . 13) (100 . "AcDbLine") (10 3020.3619909502
2100.3018891403 0.0) (11 3254.1476923077 2100.3018891403 0.0))
((0 . "LINE") (100 . "AcDbEntity") (8 . "MASONRY") (62 . 7) (370 . 13) (100 . "AcDbLine") (10 3186.2743891403
3414.4046832579 0.0) (11 3039.2155656109 3414.4046832579 0.0))
((0 . "LINE") (100 . "AcDbEntity") (8 . "MASONRY") (62 . 7) (370 . 13) (100 . "AcDbLine") (10 3046.7572850679
3472.850678733 0.0) (11 3470.9654298643 3472.850678733 0.0))
((0 . "LINE") (100 . "AcDbEntity") (8 . "MASONRY") (62 . 7) (370 . 13) (100 . "AcDbLine") (10 3048.6425339367
1346.1538461538 0.0) (11 3048.6425339367 1332.956719457 0.0))
((0 . "LINE") (100 . "AcDbEntity") (8 . "MASONRY") (62 . 7) (370 . 13) (100 . "AcDbLine") (10 3048.6425339367
1332.956719457 0.0) (11 3320.1357466063 1332.956719457 0.0))
((0 . "LINE") (100 . "AcDbEntity") (8 . "MASONRY") (62 . 7) (370 . 13) (100 . "AcDbLine") (10 3054.2986425339
2899.6981108597 0.0) (11 3054.2986425339 2933.6347624434 0.0))
((0 . "LINE") (100 . "AcDbEntity") (8 . "MASONRY") (62 . 7) (370 . 13) (100 . "AcDbLine") (10 3054.2986425339
2899.6981108597 0.0) (11 3084.4644343891 2899.6981108597 0.0))
((0 . "LINE") (100 . "AcDbEntity") (8 . "MASONRY") (62 . 7) (370 . 13) (100 . "AcDbLine") (10 3061.8403506787
3525.6412556561 0.0) (11 3061.8403506787 3536.9534728507 0.0))
((0 . "LINE") (100 . "AcDbEntity") (8 . "MASONRY") (62 . 7) (370 . 13) (100 . "AcDbLine") (10 3295.6260633484
1447.963800905 0.0) (11 3076.9230769231 1447.963800905 0.0))
((0 . "LINE") (100 . "AcDbEntity") (8 . "MASONRY") (62 . 7) (370 . 13) (100 . "AcDbLine") (10 3076.9230769231
1447.963800905 0.0) (11 3058.0695022624 1447.963800905 0.0))
((0 . "LINE") (100 . "AcDbEntity") (8 . "MASONRY") (62 . 7) (370 . 13) (100 . "AcDbLine") (10 3069.381719457
1493.2126696833 0.0) (11 3076.9230769231 1493.2126696833 0.0))
((0 . "LINE") (100 . "AcDbEntity") (8 . "MASONRY") (62 . 7) (370 . 13) (100 . "AcDbLine") (10 3084.4647850679
2337.8584502262 0.0) (11 3084.4647850679 2319.0045248869 0.0))
((0 . "LINE") (100 . "AcDbEntity") (8 . "MASONRY") (62 . 7) (370 . 13) (100 . "AcDbLine") (10 3076.9230769231
1168.9295701357 0.0) (11 3122.1719457014 1168.9295701357 0.0))
((0 . "LINE") (100 . "AcDbEntity") (8 . "MASONRY") (62 . 7) (370 . 13) (100 . "AcDbLine") (10 3092.0058031674
2462.2928393665 0.0) (11 3092.0058031674 2473.6050565611 0.0))
((0 . "LINE") (100 . "AcDbEntity") (8 . "MASONRY") (62 . 7) (370 . 13) (100 . "AcDbLine") (10 3088.2352941176
1500.7550678733 0.0) (11 3303.1674208145 1500.7550678733 0.0))
((0 . "LINE") (100 . "AcDbEntity") (8 . "MASONRY") (62 . 7) (370 . 13) (100 . "AcDbLine") (10 3088.2352941176
1025.6419457014 0.0) (11 3095.7766515837 1025.6419457014 0.0))
((0 . "LINE") (100 . "AcDbEntity") (8 . "MASONRY") (62 . 7) (370 . 13) (100 . "AcDbLine") (10 3099.5475113122
1542.2313574661 0.0) (11 3099.5475113122 1557.3161538462 0.0))
((0 . "LINE") (100 . "AcDbEntity") (8 . "MASONRY") (62 . 7) (370 . 13) (100 . "AcDbLine") (10 3095.7766515837
984.1628959276 0.0) (11 3095.7766515837 1025.6419457014 0.0))
((0 . "LINE") (100 . "AcDbEntity") (8 . "MASONRY") (62 . 7) (370 . 13) (100 . "AcDbLine") (10 3246.6063348416
1025.6419457014 0.0) (11 3095.7766515837 1025.6419457014 0.0))
((0 . "LINE") (100 . "AcDbEntity") (8 . "MASONRY") (62 . 7) (370 . 13) (100 . "AcDbLine") (10 3095.7766515837
984.1628959276 0.0) (11 3122.1719457014 984.1628959276 0.0))
((0 . "LINE") (100 . "AcDbEntity") (8 . "MASONRY") (62 . 7) (370 . 13) (100 . "AcDbLine") (10 3103.3953506787
893.665158371 0.0) (11 3103.3953506787 850.8300791855 0.0))
((0 . "LINE") (100 . "AcDbEntity") (8 . "MASONRY") (62 . 7) (370 . 13) (100 . "AcDbLine") (10 3103.3953506787
850.8300791855 0.0) (11 3174.9621719457 850.8300791855 0.0))
((0 . "LINE") (100 . "AcDbEntity") (8 . "MASONRY") (62 . 7) (370 . 13) (100 . "AcDbLine") (10 3193.8161085973
718.3257918552 0.0) (11 3144.7963800905 718.3257918552 0.0))
((0 . "LINE") (100 . "AcDbEntity") (8 . "MASONRY") (62 . 7) (370 . 13) (100 . "AcDbLine") (10 3103.3183710407
2897.8125113122 0.0) (11 3227.752760181 2897.8125113122 0.0))
((0 . "LINE") (100 . "AcDbEntity") (8 . "MASONRY") (62 . 7) (370 . 13) (100 . "AcDbLine") (10 3107.0888687783
923.8319909502 0.0) (11 3435.1431674208 923.8319909502 0.0))
((0 . "LINE") (100 . "AcDbEntity") (8 . "MASONRY") (62 . 7) (370 . 13) (100 . "AcDbLine") (10 3120.2863461538
2820.5125904977 0.0) (11 3120.2863461538 2794.1176470588 0.0))
((0 . "LINE") (100 . "AcDbEntity") (8 . "MASONRY") (62 . 7) (370 . 13) (100 . "AcDbLine") (10 3120.2863461538
2820.5125904977 0.0) (11 3291.8552036199 2820.5125904977 0.0))
((0 . "LINE") (100 . "AcDbEntity") (8 . "MASONRY") (62 . 7) (370 . 13) (100 . "AcDbLine") (10 3306.938280543
2007.9185520362 0.0) (11 3125.9428054299 2007.9185520362 0.0))
((0 . "LINE") (100 . "AcDbEntity") (8 . "MASONRY") (62 . 7) (370 . 13) (100 . "AcDbLine") (10 3125.9428054299
1889.1402714932 0.0) (11 3163.6499547511 1889.1402714932 0.0))
((0 . "LINE") (100 . "AcDbEntity") (8 . "MASONRY") (62 . 7) (370 . 13) (100 . "AcDbLine") (10 3131.5985633484
1843.8914027149 0.0) (11 3131.5985633484 1858.9741289593 0.0))
((0 . "LINE") (100 . "AcDbEntity") (8 . "MASONRY") (62 . 7) (370 . 13) (100 . "AcDbLine") (10 3133.4841628959
2251.1312217195 0.0) (11 3159.8794570136 2251.1312217195 0.0))
((0 . "LINE") (100 . "AcDbEntity") (8 . "MASONRY") (62 . 7) (370 . 13) (100 . "AcDbLine") (10 3159.8794570136
2251.1312217195 0.0) (11 3182.5038914027 2251.1312217195 0.0))
((0 . "LINE") (100 . "AcDbEntity") (8 . "MASONRY") (62 . 7) (370 . 13) (100 . "AcDbLine") (10 3131.5985633484
1858.9741289593 0.0) (11 3167.4208144796 1858.9741289593 0.0))
((0 . "LINE") (100 . "AcDbEntity") (8 . "MASONRY") (62 . 7) (370 . 13) (100 . "AcDbLine") (10 3141.025520362
1670.4383257919 0.0) (11 3141.025520362 1704.3749773756 0.0))
((0 . "LINE") (100 . "AcDbEntity") (8 . "MASONRY") (62 . 7) (370 . 13) (100 . "AcDbLine") (10 3141.025520362
1670.4383257919 0.0) (11 3306.938280543 1670.4383257919 0.0))
((0 . "LINE") (100 . "AcDbEntity") (8 . "MASONRY") (62 . 7) (370 . 13) (100 . "AcDbLine") (10 3433.257918552
1265.0088461538 0.0) (11 3288.0843438914 1265.0088461538 0.0))
((0 . "LINE") (100 . "AcDbEntity") (8 . "MASONRY") (62 . 7) (370 . 13) (100 . "AcDbLine") (10 3288.0843438914
1265.0088461538 0.0) (11 3146.681979638 1265.0088461538 0.0))
((0 . "LINE") (100 . "AcDbEntity") (8 . "MASONRY") (62 . 7) (370 . 13) (100 . "AcDbLine") (10 3146.681979638
1293.3625791855 0.0) (11 3146.681979638 1265.0088461538 0.0))
((0 . "LINE") (100 . "AcDbEntity") (8 . "MASONRY") (62 . 7) (370 . 13) (100 . "AcDbLine") (10 3148.567239819
2450.9806221719 0.0) (11 3148.567239819 2398.1900452489 0.0))
((0 . "LINE") (100 . "AcDbEntity") (8 . "MASONRY") (62 . 7) (370 . 13) (100 . "AcDbLine") (10 3148.567239819
991.7039140271 0.0) (11 3589.1412895928 991.7039140271 0.0))
((0 . "LINE") (100 . "AcDbEntity") (8 . "MASONRY") (62 . 7) (370 . 13) (100 . "AcDbLine") (10 3152.3377375566
1180.0940271493 0.0) (11 3216.517861991 1180.0940271493 0.0))
((0 . "LINE") (100 . "AcDbEntity") (8 . "MASONRY") (62 . 7) (370 . 13) (100 . "AcDbLine") (10 3180.6186312217
2130.467341629 0.0) (11 3180.6186312217 2156.8629751131 0.0))
((0 . "LINE") (100 . "AcDbEntity") (8 . "MASONRY") (62 . 7) (370 . 13) (100 . "AcDbLine") (10 3180.6186312217
2156.8629751131 0.0) (11 3291.8552036199 2156.8629751131 0.0))
((0 . "LINE") (100 . "AcDbEntity") (8 . "MASONRY") (62 . 7) (370 . 13) (100 . "AcDbLine") (10 3207.0135746606
3193.8157579186 0.0) (11 3197.5866063348 3193.8157579186 0.0))
((0 . "LINE") (100 . "AcDbEntity") (8 . "MASONRY") (62 . 7) (370 . 13) (100 . "AcDbLine") (10 3201.3574660633
1864.7048076923 0.0) (11 3220.211040724 1864.7048076923 0.0))
((0 . "LINE") (100 . "AcDbEntity") (8 . "MASONRY") (62 . 7) (370 . 13) (100 . "AcDbLine") (10 3220.211040724
1864.7048076923 0.0) (11 3452.1118438914 1864.7048076923 0.0))
((0 . "LINE") (100 . "AcDbEntity") (8 . "MASONRY") (62 . 7) (370 . 13) (100 . "AcDbLine") (10 3216.4405429864
3193.8157579186 0.0) (11 3207.0135746606 3193.8157579186 0.0))
((0 . "LINE") (100 . "AcDbEntity") (8 . "MASONRY") (62 . 7) (370 . 13) (100 . "AcDbLine") (10 3207.0135746606
3193.8157579186 0.0) (11 3207.0135746606 3231.5236085973 0.0))
((0 . "LINE") (100 . "AcDbEntity") (8 . "MASONRY") (62 . 7) (370 . 13) (100 . "AcDbLine") (10 3229.6380090498
3412.5190837104 0.0) (11 3208.8988235294 3412.5190837104 0.0))
((0 . "LINE") (100 . "AcDbEntity") (8 . "MASONRY") (62 . 7) (370 . 13) (100 . "AcDbLine") (10 3227.752760181
1134.995678733 0.0) (11 3216.517861991 1134.995678733 0.0))
((0 . "LINE") (100 . "AcDbEntity") (8 . "MASONRY") (62 . 7) (370 . 13) (100 . "AcDbLine") (10 3216.517861991
1134.995678733 0.0) (11 3216.517861991 1180.0940271493 0.0))
((0 . "LINE") (100 . "AcDbEntity") (8 . "MASONRY") (62 . 7) (370 . 13) (100 . "AcDbLine") (10 3433.257918552
1180.0940271493 0.0) (11 3216.517861991 1180.0940271493 0.0))
((0 . "LINE") (100 . "AcDbEntity") (8 . "MASONRY") (62 . 7) (370 . 13) (100 . "AcDbLine") (10 3220.211040724
2754.5248868778 0.0) (11 3220.211040724 2733.7860520362 0.0))
((0 . "LINE") (100 . "AcDbEntity") (8 . "MASONRY") (62 . 7) (370 . 13) (100 . "AcDbLine") (10 3220.211040724
2754.5248868778 0.0) (11 3340.874581448 2754.5248868778 0.0))
((0 . "LINE") (100 . "AcDbEntity") (8 . "MASONRY") (62 . 7) (370 . 13) (100 . "AcDbLine") (10 3340.874581448
2754.5248868778 0.0) (11 3352.1871493213 2754.5248868778 0.0))
((0 . "LINE") (100 . "AcDbEntity") (8 . "MASONRY") (62 . 7) (370 . 13) (100 . "AcDbLine") (10 3223.9819004525
2202.1118438914 0.0) (11 3548.2653393665 2202.1118438914 0.0))
((0 . "LINE") (100 . "AcDbEntity") (8 . "MASONRY") (62 . 7) (370 . 13) (100 . "AcDbLine") (10 3229.6380090498
3329.5623642534 0.0) (11 3229.6380090498 3263.500780543 0.0))
((0 . "LINE") (100 . "AcDbEntity") (8 . "MASONRY") (62 . 7) (370 . 13) (100 . "AcDbLine") (10 3229.6380090498
3376.6968325792 0.0) (11 3229.6380090498 3329.5623642534 0.0))
((0 . "LINE") (100 . "AcDbEntity") (8 . "MASONRY") (62 . 7) (370 . 13) (100 . "AcDbLine") (10 3344.6454298643
3263.500780543 0.0) (11 3229.6380090498 3263.500780543 0.0))
((0 . "LINE") (100 . "AcDbEntity") (8 . "MASONRY") (62 . 7) (370 . 13) (100 . "AcDbLine") (10 3227.752760181
2249.2463122172 0.0) (11 3235.2941176471 2249.2463122172 0.0))
((0 . "LINE") (100 . "AcDbEntity") (8 . "MASONRY") (62 . 7) (370 . 13) (100 . "AcDbLine") (10 3229.6380090498
3412.5190837104 0.0) (11 3265.4599095023 3412.5190837104 0.0))
((0 . "LINE") (100 . "AcDbEntity") (8 . "MASONRY") (62 . 7) (370 . 13) (100 . "AcDbLine") (10 3229.6380090498
3412.5190837104 0.0) (11 3229.6380090498 3376.6968325792 0.0))
((0 . "LINE") (100 . "AcDbEntity") (8 . "MASONRY") (62 . 7) (370 . 13) (100 . "AcDbLine") (10 3288.0843438914
3376.6968325792 0.0) (11 3229.6380090498 3376.6968325792 0.0))
((0 . "LINE") (100 . "AcDbEntity") (8 . "MASONRY") (62 . 7) (370 . 13) (100 . "AcDbLine") (10 3235.2941176471
861.1100791855 0.0) (11 3235.2941176471 874.8105429864 0.0))
((0 . "LINE") (100 . "AcDbEntity") (8 . "MASONRY") (62 . 7) (370 . 13) (100 . "AcDbLine") (10 3246.9052941176
861.1100791855 0.0) (11 3235.2941176471 861.1100791855 0.0))
((0 . "LINE") (100 . "AcDbEntity") (8 . "MASONRY") (62 . 7) (370 . 13) (100 . "AcDbLine") (10 3235.2941176471
812.996561086 0.0) (11 3235.2941176471 861.1100791855 0.0))
((0 . "LINE") (100 . "AcDbEntity") (8 . "MASONRY") (62 . 7) (370 . 13) (100 . "AcDbLine") (10 3254.1476923077
3190.0452488688 0.0) (11 3295.6260633484 3190.0452488688 0.0))
((0 . "LINE") (100 . "AcDbEntity") (8 . "MASONRY") (62 . 7) (370 . 13) (100 . "AcDbLine") (10 3259.8041515837
2620.6638800905 0.0) (11 3254.1476923077 2620.6638800905 0.0))
((0 . "LINE") (100 . "AcDbEntity") (8 . "MASONRY") (62 . 7) (370 . 13) (100 . "AcDbLine") (10 3259.8041515837
2620.6638800905 0.0) (11 3259.8041515837 2576.6191402715 0.0))
((0 . "LINE") (100 . "AcDbEntity") (8 . "MASONRY") (62 . 7) (370 . 13) (100 . "AcDbLine") (10 3344.6454298643
2576.6191402715 0.0) (11 3259.8041515837 2576.6191402715 0.0))
((0 . "LINE") (100 . "AcDbEntity") (8 . "MASONRY") (62 . 7) (370 . 13) (100 . "AcDbLine") (10 3259.8041515837
2620.6638800905 0.0) (11 3344.6454298643 2620.6638800905 0.0))
((0 . "LINE") (100 . "AcDbEntity") (8 . "MASONRY") (62 . 7) (370 . 13) (100 . "AcDbLine") (10 3276.7721266968
2100.3018891403 0.0) (11 3269.2307692308 2100.3018891403 0.0))
((0 . "LINE") (100 . "AcDbEntity") (8 . "MASONRY") (62 . 7) (370 . 13) (100 . "AcDbLine") (10 3348.4162895928
3414.4046832579 0.0) (11 3280.5429864253 3414.4046832579 0.0))
((0 . "LINE") (100 . "AcDbEntity") (8 . "MASONRY") (62 . 7) (370 . 13) (100 . "AcDbLine") (10 3280.5429864253
2894.0426923077 0.0) (11 3344.6454298643 2894.0426923077 0.0))
((0 . "LINE") (100 . "AcDbEntity") (8 . "MASONRY") (62 . 7) (370 . 13) (100 . "AcDbLine") (10 3310.7087782805
1131.221719457 0.0) (11 3280.5429864253 1131.221719457 0.0))
((0 . "LINE") (100 . "AcDbEntity") (8 . "MASONRY") (62 . 7) (370 . 13) (100 . "AcDbLine") (10 3284.3138461538
2260.483959276 0.0) (11 3431.3726696833 2260.483959276 0.0))
((0 . "LINE") (100 . "AcDbEntity") (8 . "MASONRY") (62 . 7) (370 . 13) (100 . "AcDbLine") (10 3340.8749321267
2806.5566628959 0.0) (11 3291.8552036199 2806.5566628959 0.0))
((0 . "LINE") (100 . "AcDbEntity") (8 . "MASONRY") (62 . 7) (370 . 13) (100 . "AcDbLine") (10 3291.8552036199
2806.5566628959 0.0) (11 3291.8552036199 2820.5125904977 0.0))
((0 . "LINE") (100 . "AcDbEntity") (8 . "MASONRY") (62 . 7) (370 . 13) (100 . "AcDbLine") (10 3291.8552036199
2843.1370248869 0.0) (11 3291.8552036199 2820.5125904977 0.0))
((0 . "LINE") (100 . "AcDbEntity") (8 . "MASONRY") (62 . 7) (370 . 13) (100 . "AcDbLine") (10 3687.7828054299
2100.3018891403 0.0) (11 3288.0843438914 2100.3018891403 0.0))
((0 . "LINE") (100 . "AcDbEntity") (8 . "MASONRY") (62 . 7) (370 . 13) (100 . "AcDbLine") (10 3297.5113122172
2051.281821267 0.0) (11 3297.5113122172 2062.5940384615 0.0))
((0 . "LINE") (100 . "AcDbEntity") (8 . "MASONRY") (62 . 7) (370 . 13) (100 . "AcDbLine") (10 3303.1674208145
1500.7550678733 0.0) (11 3303.1674208145 1561.0859728507 0.0))
((0 . "LINE") (100 . "AcDbEntity") (8 . "MASONRY") (62 . 7) (370 . 13) (100 . "AcDbLine") (10 3578.4314932127
1500.7550678733 0.0) (11 3303.1674208145 1500.7550678733 0.0))
((0 . "LINE") (100 . "AcDbEntity") (8 . "MASONRY") (62 . 7) (370 . 13) (100 . "AcDbLine") (10 3306.938280543
1598.7924434389 0.0) (11 3306.938280543 1606.334841629 0.0))
((0 . "LINE") (100 . "AcDbEntity") (8 . "MASONRY") (62 . 7) (370 . 13) (100 . "AcDbLine") (10 3306.938280543
1606.334841629 0.0) (11 3306.938280543 1625.1121266968 0.0))
((0 . "LINE") (100 . "AcDbEntity") (8 . "MASONRY") (62 . 7) (370 . 13) (100 . "AcDbLine") (10 3306.938280543
1625.1121266968 0.0) (11 3306.938280543 1670.4383257919 0.0))
((0 . "LINE") (100 . "AcDbEntity") (8 . "MASONRY") (62 . 7) (370 . 13) (100 . "AcDbLine") (10 3306.938280543
1670.4383257919 0.0) (11 3325.7918552036 1670.4383257919 0.0))
((0 . "LINE") (100 . "AcDbEntity") (8 . "MASONRY") (62 . 7) (370 . 13) (100 . "AcDbLine") (10 3310.7087782805
1131.221719457 0.0) (11 3310.7087782805 1116.1396832579 0.0))
((0 . "LINE") (100 . "AcDbEntity") (8 . "MASONRY") (62 . 7) (370 . 13) (100 . "AcDbLine") (10 3310.7087782805
1153.8461538462 0.0) (11 3310.7087782805 1131.221719457 0.0))
((0 . "LINE") (100 . "AcDbEntity") (8 . "MASONRY") (62 . 7) (370 . 13) (100 . "AcDbLine") (10 3310.7091289593
889.8953393665 0.0) (11 3310.7091289593 882.3529411765 0.0))
((0 . "LINE") (100 . "AcDbEntity") (8 . "MASONRY") (62 . 7) (370 . 13) (100 . "AcDbLine") (10 3310.7087782805
3110.8597285068 0.0) (11 3348.4162895928 3110.8597285068 0.0))
((0 . "LINE") (100 . "AcDbEntity") (8 . "MASONRY") (62 . 7) (370 . 13) (100 . "AcDbLine") (10 3582.2019909502
1602.7120927602 0.0) (11 3582.2019909502 1625.1121266968 0.0))
((0 . "LINE") (100 . "AcDbEntity") (8 . "MASONRY") (62 . 7) (370 . 13) (100 . "AcDbLine") (10 3582.2019909502
1625.1121266968 0.0) (11 3306.938280543 1625.1121266968 0.0))
((0 . "LINE") (100 . "AcDbEntity") (8 . "MASONRY") (62 . 7) (370 . 13) (100 . "AcDbLine") (10 3320.1357466063
1297.135158371 0.0) (11 3320.1357466063 1332.956719457 0.0))
((0 . "LINE") (100 . "AcDbEntity") (8 . "MASONRY") (62 . 7) (370 . 13) (100 . "AcDbLine") (10 3337.1040723982
3378.5824321267 0.0) (11 3322.0209954751 3378.5824321267 0.0))
((0 . "LINE") (100 . "AcDbEntity") (8 . "MASONRY") (62 . 7) (370 . 13) (100 . "AcDbLine") (10 3593.5142081448
1332.956719457 0.0) (11 3320.1357466063 1332.956719457 0.0))
((0 . "LINE") (100 . "AcDbEntity") (8 . "MASONRY") (62 . 7) (370 . 13) (100 . "AcDbLine") (10 3322.0209954751
1217.949638009 0.0) (11 3337.1040723982 1217.949638009 0.0))
((0 . "LINE") (100 . "AcDbEntity") (8 . "MASONRY") (62 . 7) (370 . 13) (100 . "AcDbLine") (10 3352.1871493213
2658.371040724 0.0) (11 3329.5627149321 2658.371040724 0.0))
((0 . "LINE") (100 . "AcDbEntity") (8 . "MASONRY") (62 . 7) (370 . 13) (100 . "AcDbLine") (10 3359.7285067873
1442.3076923077 0.0) (11 3329.5627149321 1442.3076923077 0.0))
((0 . "LINE") (100 . "AcDbEntity") (8 . "MASONRY") (62 . 7) (370 . 13) (100 . "AcDbLine") (10 3333.3332126697
1817.4971493213 0.0) (11 3567.1192760181 1817.4971493213 0.0))
((0 . "LINE") (100 . "AcDbEntity") (8 . "MASONRY") (62 . 7) (370 . 13) (100 . "AcDbLine") (10 3337.1040723982
2011.6897511312 0.0) (11 3408.7482352941 2011.6897511312 0.0))
((0 . "LINE") (100 . "AcDbEntity") (8 . "MASONRY") (62 . 7) (370 . 13) (100 . "AcDbLine") (10 3348.4162895928
3178.7330316742 0.0) (11 3348.4162895928 3193.8157579186 0.0))
((0 . "LINE") (100 . "AcDbEntity") (8 . "MASONRY") (62 . 7) (370 . 13) (100 . "AcDbLine") (10 3350.3018891403
2843.1370248869 0.0) (11 3350.3018891403 2854.4492420814 0.0))
((0 . "LINE") (100 . "AcDbEntity") (8 . "MASONRY") (62 . 7) (370 . 13) (100 . "AcDbLine") (10 3348.4162895928
1738.3116289593 0.0) (11 3363.4993665158 1738.3116289593 0.0))
((0 . "LINE") (100 . "AcDbEntity") (8 . "MASONRY") (62 . 7) (370 . 13) (100 . "AcDbLine") (10 3348.4162895928
1670.4383257919 0.0) (11 3378.582081448 1670.4383257919 0.0))
((0 . "LINE") (100 . "AcDbEntity") (8 . "MASONRY") (62 . 7) (370 . 13) (100 . "AcDbLine") (10 3465.309321267
823.9069457014 0.0) (11 3348.4162895928 823.9069457014 0.0))
((0 . "LINE") (100 . "AcDbEntity") (8 . "MASONRY") (62 . 7) (370 . 13) (100 . "AcDbLine") (10 3352.1871493213
3152.3380882353 0.0) (11 3352.1871493213 3159.8791063348 0.0))
((0 . "LINE") (100 . "AcDbEntity") (8 . "MASONRY") (62 . 7) (370 . 13) (100 . "AcDbLine") (10 3371.0407239819
1451.5803393665 0.0) (11 3578.4314932127 1451.5803393665 0.0))
((0 . "LINE") (100 . "AcDbEntity") (8 . "MASONRY") (62 . 7) (370 . 13) (100 . "AcDbLine") (10 3393.665158371
1674.2081447964 0.0) (11 3412.5187330317 1674.2081447964 0.0))
((0 . "LINE") (100 . "AcDbEntity") (8 . "MASONRY") (62 . 7) (370 . 13) (100 . "AcDbLine") (10 3563.0812104072
785.4264932127 0.0) (11 3563.0812104072 812.6092307692 0.0))
((0 . "LINE") (100 . "AcDbEntity") (8 . "MASONRY") (62 . 7) (370 . 13) (100 . "AcDbLine") (10 3563.0812104072
814.1289366516 0.0) (11 3563.0812104072 814.4727375566 0.0))
((0 . "LINE") (100 . "AcDbEntity") (8 . "MASONRY") (62 . 7) (370 . 13) (100 . "AcDbLine") (10 3563.0812104072
814.4727375566 0.0) (11 3555.8067081448 814.4727375566 0.0))
((0 . "LINE") (100 . "AcDbEntity") (8 . "MASONRY") (62 . 7) (370 . 13) (100 . "AcDbLine") (10 3555.8067081448
814.4727375566 0.0) (11 3444.3450565611 814.4727375566 0.0))
((0 . "LINE") (100 . "AcDbEntity") (8 . "MASONRY") (62 . 7) (370 . 13) (100 . "AcDbLine") (10 3444.3450565611
814.4727375566 0.0) (11 3444.3450565611 658.2877262443 0.0))
((0 . "LINE") (100 . "AcDbEntity") (8 . "MASONRY") (62 . 7) (370 . 13) (100 . "AcDbLine") (10 3555.8070588235
1738.163178733 0.0) (11 3435.1431674208 1738.163178733 0.0))
((0 . "LINE") (100 . "AcDbEntity") (8 . "MASONRY") (62 . 7) (370 . 13) (100 . "AcDbLine") (10 3435.1431674208
1738.163178733 0.0) (11 3416.8916628959 1738.163178733 0.0))
((0 . "LINE") (100 . "AcDbEntity") (8 . "MASONRY") (62 . 7) (370 . 13) (100 . "AcDbLine") (10 3416.8916628959
1738.163178733 0.0) (11 3416.8916628959 1711.9146153846 0.0))
((0 . "LINE") (100 . "AcDbEntity") (8 . "MASONRY") (62 . 7) (370 . 13) (100 . "AcDbLine") (10 3423.8309502262
889.8953393665 0.0) (11 3435.1431674208 889.8953393665 0.0))
((0 . "LINE") (100 . "AcDbEntity") (8 . "MASONRY") (62 . 7) (370 . 13) (100 . "AcDbLine") (10 3431.3726696833
2239.8190045249 0.0) (11 3431.3726696833 2260.483959276 0.0))
((0 . "LINE") (100 . "AcDbEntity") (8 . "MASONRY") (62 . 7) (370 . 13) (100 . "AcDbLine") (10 3616.1386425339
2260.483959276 0.0) (11 3544.494841629 2260.483959276 0.0))
((0 . "LINE") (100 . "AcDbEntity") (8 . "MASONRY") (62 . 7) (370 . 13) (100 . "AcDbLine") (10 3544.494841629
2260.483959276 0.0) (11 3431.3726696833 2260.483959276 0.0))
((0 . "LINE") (100 . "AcDbEntity") (8 . "MASONRY") (62 . 7) (370 . 13) (100 . "AcDbLine") (10 3653.9973642534
1199.0950226244 0.0) (11 3653.9973642534 1180.0940271493 0.0))
((0 . "LINE") (100 . "AcDbEntity") (8 . "MASONRY") (62 . 7) (370 . 13) (100 . "AcDbLine") (10 3653.9973642534
1180.0940271493 0.0) (11 3433.257918552 1180.0940271493 0.0))
((0 . "LINE") (100 . "AcDbEntity") (8 . "MASONRY") (62 . 7) (370 . 13) (100 . "AcDbLine") (10 3433.257918552
1265.0088461538 0.0) (11 3433.257918552 1180.0940271493 0.0))
((0 . "LINE") (100 . "AcDbEntity") (8 . "MASONRY") (62 . 7) (370 . 13) (100 . "AcDbLine") (10 3433.257918552
1265.0088461538 0.0) (11 3618.0239027149 1265.0088461538 0.0))
((0 . "LINE") (100 . "AcDbEntity") (8 . "MASONRY") (62 . 7) (370 . 13) (100 . "AcDbLine") (10 3435.1431674208
942.6838461538 0.0) (11 3435.1431674208 923.8319909502 0.0))
((0 . "LINE") (100 . "AcDbEntity") (8 . "MASONRY") (62 . 7) (370 . 13) (100 . "AcDbLine") (10 3435.1431674208
923.8319909502 0.0) (11 3435.1431674208 889.8953393665 0.0))
((0 . "LINE") (100 . "AcDbEntity") (8 . "MASONRY") (62 . 7) (370 . 13) (100 . "AcDbLine") (10 3450.2262443439
889.8953393665 0.0) (11 3435.1431674208 889.8953393665 0.0))
((0 . "LINE") (100 . "AcDbEntity") (8 . "MASONRY") (62 . 7) (370 . 13) (100 . "AcDbLine") (10 3452.1118438914
1864.7048076923 0.0) (11 3452.1118438914 1896.681979638 0.0))
((0 . "LINE") (100 . "AcDbEntity") (8 . "MASONRY") (62 . 7) (370 . 13) (100 . "AcDbLine") (10 3608.5972850679
1864.7048076923 0.0) (11 3452.1118438914 1864.7048076923 0.0))
((0 . "LINE") (100 . "AcDbEntity") (8 . "MASONRY") (62 . 7) (370 . 13) (100 . "AcDbLine") (10 3470.9654298643
3435.1435180995 0.0) (11 3470.9654298643 3472.850678733 0.0))
((0 . "LINE") (100 . "AcDbEntity") (8 . "MASONRY") (62 . 7) (370 . 13) (100 . "AcDbLine") (10 3704.7511312217
3472.850678733 0.0) (11 3470.9654298643 3472.850678733 0.0))
((0 . "LINE") (100 . "AcDbEntity") (8 . "MASONRY") (62 . 7) (370 . 13) (100 . "AcDbLine") (10 3472.850678733
1404.6771719457 0.0) (11 3736.8021832579 1404.6771719457 0.0))
((0 . "LINE") (100 . "AcDbEntity") (8 . "MASONRY") (62 . 7) (370 . 13) (100 . "AcDbLine") (10 3736.8021832579
1404.6771719457 0.0) (11 3736.8021832579 1432.8817647059 0.0))
((0 . "LINE") (100 . "AcDbEntity") (8 . "MASONRY") (62 . 7) (370 . 13) (100 . "AcDbLine") (10 3499.2459728507
2492.4582918552 0.0) (11 3484.1628959276 2492.4582918552 0.0))
((0 . "LINE") (100 . "AcDbEntity") (8 . "MASONRY") (62 . 7) (370 . 13) (100 . "AcDbLine") (10 3535.7994004525
585.8256447964 0.0) (11 3619.9095022624 585.8256447964 0.0))
((0 . "LINE") (100 . "AcDbEntity") (8 . "MASONRY") (62 . 7) (370 . 13) (100 . "AcDbLine") (10 3619.9095022624
585.8256447964 0.0) (11 3673.9145701357 585.8256447964 0.0))
((0 . "LINE") (100 . "AcDbEntity") (8 . "MASONRY") (62 . 7) (370 . 13) (100 . "AcDbLine") (10 3499.2459728507
2492.4582918552 0.0) (11 3499.2459728507 2473.6050565611 0.0))
((0 . "LINE") (100 . "AcDbEntity") (8 . "MASONRY") (62 . 7) (370 . 13) (100 . "AcDbLine") (10 3499.2459728507
2492.4582918552 0.0) (11 3540.7239819005 2492.4582918552 0.0))
((0 . "LINE") (100 . "AcDbEntity") (8 . "MASONRY") (62 . 7) (370 . 13) (100 . "AcDbLine") (10 3535.0678733032
897.4349773756 0.0) (11 3499.2459728507 897.4349773756 0.0))
((0 . "LINE") (100 . "AcDbEntity") (8 . "MASONRY") (62 . 7) (370 . 13) (100 . "AcDbLine") (10 3503.0164705882
2013.5746606335 0.0) (11 3578.4314932127 2013.5746606335 0.0))
((0 . "LINE") (100 . "AcDbEntity") (8 . "MASONRY") (62 . 7) (370 . 13) (100 . "AcDbLine") (10 3589.1412895928
991.7039140271 0.0) (11 3589.1412895928 1036.9541628959 0.0))
((0 . "LINE") (100 . "AcDbEntity") (8 . "MASONRY") (62 . 7) (370 . 13) (100 . "AcDbLine") (10 3589.1412895928
1036.9541628959 0.0) (11 3570.8897737557 1036.9541628959 0.0))
((0 . "LINE") (100 . "AcDbEntity") (8 . "MASONRY") (62 . 7) (370 . 13) (100 . "AcDbLine") (10 3570.8897737557
1036.9541628959 0.0) (11 3506.7873303167 1036.9541628959 0.0))
((0 . "LINE") (100 . "AcDbEntity") (8 . "MASONRY") (62 . 7) (370 . 13) (100 . "AcDbLine") (10 3606.7085746606
2320.8894343891 0.0) (11 3523.7556561086 2320.8894343891 0.0))
((0 . "LINE") (100 . "AcDbEntity") (8 . "MASONRY") (62 . 7) (370 . 13) (100 . "AcDbLine") (10 3523.7556561086
2320.8894343891 0.0) (11 3523.7556561086 2296.3800904977 0.0))
((0 . "LINE") (100 . "AcDbEntity") (8 . "MASONRY") (62 . 7) (370 . 13) (100 . "AcDbLine") (10 3606.7085746606
2320.8894343891 0.0) (11 3606.7085746606 2378.1319909502 0.0))
((0 . "LINE") (100 . "AcDbEntity") (8 . "MASONRY") (62 . 7) (370 . 13) (100 . "AcDbLine") (10 3606.7085746606
2378.1319909502 0.0) (11 3518.0995475113 2378.1319909502 0.0))
((0 . "LINE") (100 . "AcDbEntity") (8 . "MASONRY") (62 . 7) (370 . 13) (100 . "AcDbLine") (10 3518.0995475113
2349.1706674208 0.0) (11 3518.0995475113 2378.1319909502 0.0))
((0 . "LINE") (100 . "AcDbEntity") (8 . "MASONRY") (62 . 7) (370 . 13) (100 . "AcDbLine") (10 3585.9728506787
881.07010181 0.0) (11 3535.0678733032 881.07010181 0.0))
((0 . "LINE") (100 . "AcDbEntity") (8 . "MASONRY") (62 . 7) (370 . 13) (100 . "AcDbLine") (10 3535.0678733032
881.07010181 0.0) (11 3535.0678733032 897.4349773756 0.0))
((0 . "LINE") (100 . "AcDbEntity") (8 . "MASONRY") (62 . 7) (370 . 13) (100 . "AcDbLine") (10 3672.6997285068
897.4349773756 0.0) (11 3535.0678733032 897.4349773756 0.0))
((0 . "LINE") (100 . "AcDbEntity") (8 . "MASONRY") (62 . 7) (370 . 13) (100 . "AcDbLine") (10 4096.9082239819
2198.3406447964 0.0) (11 3563.3484162896 2198.3406447964 0.0))
((0 . "LINE") (100 . "AcDbEntity") (8 . "MASONRY") (62 . 7) (370 . 13) (100 . "AcDbLine") (10 3578.4314932127
1500.7550678733 0.0) (11 3578.4314932127 1451.5803393665 0.0))
((0 . "LINE") (100 . "AcDbEntity") (8 . "MASONRY") (62 . 7) (370 . 13) (100 . "AcDbLine") (10 3578.4314932127
1500.7550678733 0.0) (11 3578.4314932127 1515.8371040724 0.0))
((0 . "LINE") (100 . "AcDbEntity") (8 . "MASONRY") (62 . 7) (370 . 13) (100 . "AcDbLine") (10 3595.3994683258
1738.3116289593 0.0) (11 3574.6606334842 1738.3116289593 0.0))
((0 . "LINE") (100 . "AcDbEntity") (8 . "MASONRY") (62 . 7) (370 . 13) (100 . "AcDbLine") (10 3800.9049773756
1817.4971493213 0.0) (11 3782.0514027149 1817.4971493213 0.0))
((0 . "LINE") (100 . "AcDbEntity") (8 . "MASONRY") (62 . 7) (370 . 13) (100 . "AcDbLine") (10 3782.0514027149
1817.4971493213 0.0) (11 3578.4314932127 1817.4971493213 0.0))
((0 . "LINE") (100 . "AcDbEntity") (8 . "MASONRY") (62 . 7) (370 . 13) (100 . "AcDbLine") (10 3582.2019909502
1557.3161538462 0.0) (11 3582.2019909502 1602.7120927602 0.0))
((0 . "LINE") (100 . "AcDbEntity") (8 . "MASONRY") (62 . 7) (370 . 13) (100 . "AcDbLine") (10 3582.2019909502
1602.7120927602 0.0) (11 3634.9925791855 1602.7120927602 0.0))
((0 . "LINE") (100 . "AcDbEntity") (8 . "MASONRY") (62 . 7) (370 . 13) (100 . "AcDbLine") (10 3634.9925791855
1602.7120927602 0.0) (11 3750 1602.7120927602 0.0))
((0 . "LINE") (100 . "AcDbEntity") (8 . "MASONRY") (62 . 7) (370 . 13) (100 . "AcDbLine") (10 3872.549479638
2511.3122171946 0.0) (11 3585.9728506787 2511.3122171946 0.0))
((0 . "LINE") (100 . "AcDbEntity") (8 . "MASONRY") (62 . 7) (370 . 13) (100 . "AcDbLine") (10 3585.9728506787
2053.1674208145 0.0) (11 3719.8338574661 2053.1674208145 0.0))
((0 . "LINE") (100 . "AcDbEntity") (8 . "MASONRY") (62 . 7) (370 . 13) (100 . "AcDbLine") (10 3578.4314932127
1451.5803393665 0.0) (11 3736.8021832579 1451.5803393665 0.0))
((0 . "LINE") (100 . "AcDbEntity") (8 . "MASONRY") (62 . 7) (370 . 13) (100 . "AcDbLine") (10 3736.8021832579
1451.5803393665 0.0) (11 3736.8021832579 1432.8817647059 0.0))
((0 . "LINE") (100 . "AcDbEntity") (8 . "MASONRY") (62 . 7) (370 . 13) (100 . "AcDbLine") (10 3597.2850678733
3412.5190837104 0.0) (11 3597.2850678733 3382.3529411765 0.0))
((0 . "LINE") (100 . "AcDbEntity") (8 . "MASONRY") (62 . 7) (370 . 13) (100 . "AcDbLine") (10 3815.9883936652
3254.1480429864 0.0) (11 3589.7437104072 3254.1480429864 0.0))
((0 . "LINE") (100 . "AcDbEntity") (8 . "MASONRY") (62 . 7) (370 . 13) (100 . "AcDbLine") (10 3589.7437104072
3050.5281334842 0.0) (11 3623.680361991 3050.5281334842 0.0))
((0 . "LINE") (100 . "AcDbEntity") (8 . "MASONRY") (62 . 7) (370 . 13) (100 . "AcDbLine") (10 3589.7437104072
2818.5496606335 0.0) (11 3619.3074321267 2818.5496606335 0.0))
((0 . "LINE") (100 . "AcDbEntity") (8 . "MASONRY") (62 . 7) (370 . 13) (100 . "AcDbLine") (10 3619.3074321267
2818.5496606335 0.0) (11 3619.3074321267 2775.2637217195 0.0))
((0 . "LINE") (100 . "AcDbEntity") (8 . "MASONRY") (62 . 7) (370 . 13) (100 . "AcDbLine") (10 3655.6544230769
2635.7466063348 0.0) (11 3655.6544230769 2600.5271153846 0.0))
((0 . "LINE") (100 . "AcDbEntity") (8 . "MASONRY") (62 . 7) (370 . 13) (100 . "AcDbLine") (10 3655.6544230769
2600.5271153846 0.0) (11 3589.7437104072 2600.5271153846 0.0))
((0 . "LINE") (100 . "AcDbEntity") (8 . "MASONRY") (62 . 7) (370 . 13) (100 . "AcDbLine") (10 3589.1412895928
991.7039140271 0.0) (11 3729.2608144796 991.7039140271 0.0))
((0 . "LINE") (100 . "AcDbEntity") (8 . "MASONRY") (62 . 7) (370 . 13) (100 . "AcDbLine") (10 3596.0018778281
509.0497737557 0.0) (11 3596.0018778281 497.7375565611 0.0))
((0 . "LINE") (100 . "AcDbEntity") (8 . "MASONRY") (62 . 7) (370 . 13) (100 . "AcDbLine") (10 3673.9145701357
497.7375565611 0.0) (11 3673.9145701357 585.8256447964 0.0))
((0 . "LINE") (100 . "AcDbEntity") (8 . "MASONRY") (62 . 7) (370 . 13) (100 . "AcDbLine") (10 3593.5142081448
3182.503540724 0.0) (11 3604.8264253394 3182.503540724 0.0))
((0 . "LINE") (100 . "AcDbEntity") (8 . "MASONRY") (62 . 7) (370 . 13) (100 . "AcDbLine") (10 3604.8264253394
3122.1719457014 0.0) (11 3604.8264253394 3182.503540724 0.0))
((0 . "LINE") (100 . "AcDbEntity") (8 . "MASONRY") (62 . 7) (370 . 13) (100 . "AcDbLine") (10 3616.1386425339
2995.8526470588 0.0) (11 3593.5142081448 2995.8526470588 0.0))
((0 . "LINE") (100 . "AcDbEntity") (8 . "MASONRY") (62 . 7) (370 . 13) (100 . "AcDbLine") (10 3593.5142081448
2635.7466063348 0.0) (11 3655.6544230769 2635.7466063348 0.0))
((0 . "LINE") (100 . "AcDbEntity") (8 . "MASONRY") (62 . 7) (370 . 13) (100 . "AcDbLine") (10 3653.8427036199
2533.9366515837 0.0) (11 3653.8427036199 2554.0741063348 0.0))
((0 . "LINE") (100 . "AcDbEntity") (8 . "MASONRY") (62 . 7) (370 . 13) (100 . "AcDbLine") (10 3653.8427036199
2554.0741063348 0.0) (11 3593.5142081448 2554.0741063348 0.0))
((0 . "LINE") (100 . "AcDbEntity") (8 . "MASONRY") (62 . 7) (370 . 13) (100 . "AcDbLine") (10 3595.3994683258
1738.3116289593 0.0) (11 3595.3994683258 1764.7058823529 0.0))
((0 . "LINE") (100 . "AcDbEntity") (8 . "MASONRY") (62 . 7) (370 . 13) (100 . "AcDbLine") (10 3981.9004524887
2894.0426923077 0.0) (11 3597.2850678733 2894.0426923077 0.0))
((0 . "LINE") (100 . "AcDbEntity") (8 . "MASONRY") (62 . 7) (370 . 13) (100 . "AcDbLine") (10 3595.3994683258
1738.3116289593 0.0) (11 3619.9095022624 1738.3116289593 0.0))
((0 . "LINE") (100 . "AcDbEntity") (8 . "MASONRY") (62 . 7) (370 . 13) (100 . "AcDbLine") (10 3970.5882352941
1934.2821266968 0.0) (11 3721.8675565611 1934.2821266968 0.0))
((0 . "LINE") (100 . "AcDbEntity") (8 . "MASONRY") (62 . 7) (370 . 13) (100 . "AcDbLine") (10 3721.8675565611
1934.2821266968 0.0) (11 3706.6363800905 1934.2821266968 0.0))
((0 . "LINE") (100 . "AcDbEntity") (8 . "MASONRY") (62 . 7) (370 . 13) (100 . "AcDbLine") (10 3706.6363800905
1934.2821266968 0.0) (11 3601.0559276018 1934.2821266968 0.0))
((0 . "LINE") (100 . "AcDbEntity") (8 . "MASONRY") (62 . 7) (370 . 13) (100 . "AcDbLine") (10 3601.0559276018
727.751719457 0.0) (11 4110.106040724 727.751719457 0.0))
((0 . "LINE") (100 . "AcDbEntity") (8 . "MASONRY") (62 . 7) (370 . 13) (100 . "AcDbLine") (10 3604.8264253394
2963.8009049774 0.0) (11 3604.8264253394 2944.946979638 0.0))
((0 . "LINE") (100 . "AcDbEntity") (8 . "MASONRY") (62 . 7) (370 . 13) (100 . "AcDbLine") (10 3606.7085746606
2320.8894343891 0.0) (11 3783.9366515837 2320.8894343891 0.0))
((0 . "LINE") (100 . "AcDbEntity") (8 . "MASONRY") (62 . 7) (370 . 13) (100 . "AcDbLine") (10 3608.5972850679
1332.956719457 0.0) (11 3619.9095022624 1332.956719457 0.0))
((0 . "LINE") (100 . "AcDbEntity") (8 . "MASONRY") (62 . 7) (370 . 13) (100 . "AcDbLine") (10 3634.9925791855
531.6742081448 0.0) (11 3608.5972850679 531.6742081448 0.0))
((0 . "LINE") (100 . "AcDbEntity") (8 . "MASONRY") (62 . 7) (370 . 13) (100 . "AcDbLine") (10 3612.3681447964
2420.814479638 0.0) (11 3612.3681447964 2458.5216402715 0.0))
((0 . "LINE") (100 . "AcDbEntity") (8 . "MASONRY") (62 . 7) (370 . 13) (100 . "AcDbLine") (10 3604.8264253394
3182.503540724 0.0) (11 3650.0752941176 3182.503540724 0.0))
((0 . "LINE") (100 . "AcDbEntity") (8 . "MASONRY") (62 . 7) (370 . 13) (100 . "AcDbLine") (10 3981.9004524887
1265.0088461538 0.0) (11 3618.0239027149 1265.0088461538 0.0))
((0 . "LINE") (100 . "AcDbEntity") (8 . "MASONRY") (62 . 7) (370 . 13) (100 . "AcDbLine") (10 3618.0239027149
1293.3625791855 0.0) (11 3618.0239027149 1265.0088461538 0.0))
((0 . "LINE") (100 . "AcDbEntity") (8 . "MASONRY") (62 . 7) (370 . 13) (100 . "AcDbLine") (10 3889.5171153846
805.1117081448 0.0) (11 3868.778280543 805.1117081448 0.0))
((0 . "LINE") (100 . "AcDbEntity") (8 . "MASONRY") (62 . 7) (370 . 13) (100 . "AcDbLine") (10 3868.778280543
805.1117081448 0.0) (11 3623.680361991 805.1117081448 0.0))
((0 . "LINE") (100 . "AcDbEntity") (8 . "MASONRY") (62 . 7) (370 . 13) (100 . "AcDbLine") (10 3631.221719457
2243.5895135747 0.0) (11 3793.363959276 2243.5895135747 0.0))
((0 . "LINE") (100 . "AcDbEntity") (8 . "MASONRY") (62 . 7) (370 . 13) (100 . "AcDbLine") (10 3638.7630769231
3416.2895927602 0.0) (11 3680.2414479638 3416.2895927602 0.0))
((0 . "LINE") (100 . "AcDbEntity") (8 . "MASONRY") (62 . 7) (370 . 13) (100 . "AcDbLine") (10 3638.7630769231
3337.1040723982 0.0) (11 3810.3315950226 3337.1040723982 0.0))
((0 . "LINE") (100 . "AcDbEntity") (8 . "MASONRY") (62 . 7) (370 . 13) (100 . "AcDbLine") (10 3758.1437782805
1739.5199095023 0.0) (11 3642.5339366516 1739.5199095023 0.0))
((0 . "LINE") (100 . "AcDbEntity") (8 . "MASONRY") (62 . 7) (370 . 13) (100 . "AcDbLine") (10 3646.3047963801
2780.920520362 0.0) (11 3748.1147511312 2780.920520362 0.0))
((0 . "LINE") (100 . "AcDbEntity") (8 . "MASONRY") (62 . 7) (370 . 13) (100 . "AcDbLine") (10 3655.6544230769
2635.7466063348 0.0) (11 3940.4227828054 2635.7466063348 0.0))
((0 . "LINE") (100 . "AcDbEntity") (8 . "MASONRY") (62 . 7) (370 . 13) (100 . "AcDbLine") (10 3657.6170135747
1157.6159728507 0.0) (11 3657.6170135747 1150.0763348416 0.0))
((0 . "LINE") (100 . "AcDbEntity") (8 . "MASONRY") (62 . 7) (370 . 13) (100 . "AcDbLine") (10 3661.3875113122
3188.1603393665 0.0) (11 4000.7536877828 3188.1603393665 0.0))
((0 . "LINE") (100 . "AcDbEntity") (8 . "MASONRY") (62 . 7) (370 . 13) (100 . "AcDbLine") (10 3725.4903167421
1336.7265384615 0.0) (11 3668.9292307692 1336.7265384615 0.0))
((0 . "LINE") (100 . "AcDbEntity") (8 . "MASONRY") (62 . 7) (370 . 13) (100 . "AcDbLine") (10 3887.6315158371
859.7285067873 0.0) (11 3684.0119457014 859.7285067873 0.0))
((0 . "LINE") (100 . "AcDbEntity") (8 . "MASONRY") (62 . 7) (370 . 13) (100 . "AcDbLine") (10 3684.0119457014
859.7285067873 0.0) (11 3668.9292307692 859.7285067873 0.0))
((0 . "LINE") (100 . "AcDbEntity") (8 . "MASONRY") (62 . 7) (370 . 13) (100 . "AcDbLine") (10 3676.4705882353
3052.3364027149 0.0) (11 3750 3052.3364027149 0.0))
((0 . "LINE") (100 . "AcDbEntity") (8 . "MASONRY") (62 . 7) (370 . 13) (100 . "AcDbLine") (10 3704.7511312217
3472.850678733 0.0) (11 3780.1661425339 3472.850678733 0.0))
((0 . "LINE") (100 . "AcDbEntity") (8 . "MASONRY") (62 . 7) (370 . 13) (100 . "AcDbLine") (10 3704.7511312217
3487.9334049774 0.0) (11 3704.7511312217 3472.850678733 0.0))
((0 . "LINE") (100 . "AcDbEntity") (8 . "MASONRY") (62 . 7) (370 . 13) (100 . "AcDbLine") (10 3710.407239819
3529.4117647059 0.0) (11 3963.0472171946 3529.4117647059 0.0))
((0 . "LINE") (100 . "AcDbEntity") (8 . "MASONRY") (62 . 7) (370 . 13) (100 . "AcDbLine") (10 3719.8338574661
1990.9502262443 0.0) (11 3719.8338574661 2053.1674208145 0.0))
((0 . "LINE") (100 . "AcDbEntity") (8 . "MASONRY") (62 . 7) (370 . 13) (100 . "AcDbLine") (10 3800.3029072398
2053.1674208145 0.0) (11 3719.8338574661 2053.1674208145 0.0))
((0 . "LINE") (100 . "AcDbEntity") (8 . "MASONRY") (62 . 7) (370 . 13) (100 . "AcDbLine") (10 3736.8025339367
585.8256447964 0.0) (11 3673.9145701357 585.8256447964 0.0))
((0 . "LINE") (100 . "AcDbEntity") (8 . "MASONRY") (62 . 7) (370 . 13) (100 . "AcDbLine") (10 3731.1464253394
1070.8908144796 0.0) (11 3731.1464253394 1099.0940271493 0.0))
((0 . "LINE") (100 . "AcDbEntity") (8 . "MASONRY") (62 . 7) (370 . 13) (100 . "AcDbLine") (10 4098.7938235294
1074.7352036199 0.0) (11 3980.0117420814 1074.7352036199 0.0))
((0 . "LINE") (100 . "AcDbEntity") (8 . "MASONRY") (62 . 7) (370 . 13) (100 . "AcDbLine") (10 3980.0117420814
1074.7352036199 0.0) (11 3980.0117420814 1099.0940271493 0.0))
((0 . "LINE") (100 . "AcDbEntity") (8 . "MASONRY") (62 . 7) (370 . 13) (100 . "AcDbLine") (10 3980.0117420814
1099.0940271493 0.0) (11 3731.1464253394 1099.0940271493 0.0))
((0 . "LINE") (100 . "AcDbEntity") (8 . "MASONRY") (62 . 7) (370 . 13) (100 . "AcDbLine") (10 3751.8852488688
2092.7601809955 0.0) (11 3729.2608144796 2092.7601809955 0.0))
((0 . "LINE") (100 . "AcDbEntity") (8 . "MASONRY") (62 . 7) (370 . 13) (100 . "AcDbLine") (10 3729.2608144796
991.7039140271 0.0) (11 3729.2608144796 1033.1815837104 0.0))
((0 . "LINE") (100 . "AcDbEntity") (8 . "MASONRY") (62 . 7) (370 . 13) (100 . "AcDbLine") (10 3729.2608144796
991.7039140271 0.0) (11 4038.4615384615 991.7039140271 0.0))
((0 . "LINE") (100 . "AcDbEntity") (8 . "MASONRY") (62 . 7) (370 . 13) (100 . "AcDbLine") (10 3750 3052.3364027149 0.0)
(11 3970.5882352941 3052.3364027149 0.0))
((0 . "LINE") (100 . "AcDbEntity") (8 . "MASONRY") (62 . 7) (370 . 13) (100 . "AcDbLine") (10 3970.5882352941
3052.3364027149 0.0) (11 3996.9838687783 3052.3364027149 0.0))
((0 . "LINE") (100 . "AcDbEntity") (8 . "MASONRY") (62 . 7) (370 . 13) (100 . "AcDbLine") (10 3750 3073.1525678733 0.0)
(11 3750 3052.3364027149 0.0))
((0 . "LINE") (100 . "AcDbEntity") (8 . "MASONRY") (62 . 7) (370 . 13) (100 . "AcDbLine") (10 3981.9004524887
1602.7120927602 0.0) (11 3782.0514027149 1602.7120927602 0.0))
((0 . "LINE") (100 . "AcDbEntity") (8 . "MASONRY") (62 . 7) (370 . 13) (100 . "AcDbLine") (10 3782.0514027149
1602.7120927602 0.0) (11 3750 1602.7120927602 0.0))
((0 . "LINE") (100 . "AcDbEntity") (8 . "MASONRY") (62 . 7) (370 . 13) (100 . "AcDbLine") (10 3750 1636.5016742081 0.0)
(11 3750 1602.7120927602 0.0))
((0 . "LINE") (100 . "AcDbEntity") (8 . "MASONRY") (62 . 7) (370 . 13) (100 . "AcDbLine") (10 3893.2883144796
1432.8817647059 0.0) (11 3736.8021832579 1432.8817647059 0.0))
((0 . "LINE") (100 . "AcDbEntity") (8 . "MASONRY") (62 . 7) (370 . 13) (100 . "AcDbLine") (10 3751.8852488688
1336.7265384615 0.0) (11 4019.6083031674 1336.7265384615 0.0))
((0 . "LINE") (100 . "AcDbEntity") (8 . "MASONRY") (62 . 7) (370 . 13) (100 . "AcDbLine") (10 3785.821561086
3137.2546719457 0.0) (11 3759.4269683258 3137.2546719457 0.0))
((0 . "LINE") (100 . "AcDbEntity") (8 . "MASONRY") (62 . 7) (370 . 13) (100 . "AcDbLine") (10 3758.1437782805
1739.5199095023 0.0) (11 3758.1437782805 1677.9793438914 0.0))
((0 . "LINE") (100 . "AcDbEntity") (8 . "MASONRY") (62 . 7) (370 . 13) (100 . "AcDbLine") (10 3758.1437782805
1677.9793438914 0.0) (11 3782.0514027149 1677.9793438914 0.0))
((0 . "LINE") (100 . "AcDbEntity") (8 . "MASONRY") (62 . 7) (370 . 13) (100 . "AcDbLine") (10 3795.2488687783
1739.5199095023 0.0) (11 3758.1437782805 1739.5199095023 0.0))
((0 . "LINE") (100 . "AcDbEntity") (8 . "MASONRY") (62 . 7) (370 . 13) (100 . "AcDbLine") (10 3800.3029072398
2053.1674208145 0.0) (11 3800.3029072398 2090.7979411765 0.0))
((0 . "LINE") (100 . "AcDbEntity") (8 . "MASONRY") (62 . 7) (370 . 13) (100 . "AcDbLine") (10 3800.3029072398
2090.7979411765 0.0) (11 3770.7391855204 2090.7979411765 0.0))
((0 . "LINE") (100 . "AcDbEntity") (8 . "MASONRY") (62 . 7) (370 . 13) (100 . "AcDbLine") (10 3780.1661425339
3472.850678733 0.0) (11 3936.6515837104 3472.850678733 0.0))
((0 . "LINE") (100 . "AcDbEntity") (8 . "MASONRY") (62 . 7) (370 . 13) (100 . "AcDbLine") (10 3780.1661425339
3472.850678733 0.0) (11 3780.1661425339 3487.9334049774 0.0))
((0 . "LINE") (100 . "AcDbEntity") (8 . "MASONRY") (62 . 7) (370 . 13) (100 . "AcDbLine") (10 4000.7536877828
3103.318020362 0.0) (11 3778.2805429864 3103.318020362 0.0))
((0 . "LINE") (100 . "AcDbEntity") (8 . "MASONRY") (62 . 7) (370 . 13) (100 . "AcDbLine") (10 3838.6128280543
1070.8908144796 0.0) (11 3778.2805429864 1070.8908144796 0.0))
((0 . "LINE") (100 . "AcDbEntity") (8 . "MASONRY") (62 . 7) (370 . 13) (100 . "AcDbLine") (10 4038.4615384615
2520.7395248869 0.0) (11 4038.4615384615 2424.5849886878 0.0))
((0 . "LINE") (100 . "AcDbEntity") (8 . "MASONRY") (62 . 7) (370 . 13) (100 . "AcDbLine") (10 4038.4615384615
2424.5849886878 0.0) (11 4038.4615384615 2404.4482239819 0.0))
((0 . "LINE") (100 . "AcDbEntity") (8 . "MASONRY") (62 . 7) (370 . 13) (100 . "AcDbLine") (10 4038.4615384615
2404.4482239819 0.0) (11 3782.0514027149 2404.4482239819 0.0))
((0 . "LINE") (100 . "AcDbEntity") (8 . "MASONRY") (62 . 7) (370 . 13) (100 . "AcDbLine") (10 3797.1337782805
2320.8894343891 0.0) (11 3783.9366515837 2320.8894343891 0.0))
((0 . "LINE") (100 . "AcDbEntity") (8 . "MASONRY") (62 . 7) (370 . 13) (100 . "AcDbLine") (10 3783.9366515837
2352.9411764706 0.0) (11 3783.9366515837 2320.8894343891 0.0))
((0 . "LINE") (100 . "AcDbEntity") (8 . "MASONRY") (62 . 7) (370 . 13) (100 . "AcDbLine") (10 3823.5294117647
2771.4932126697 0.0) (11 3793.363959276 2771.4932126697 0.0))
((0 . "LINE") (100 . "AcDbEntity") (8 . "MASONRY") (62 . 7) (370 . 13) (100 . "AcDbLine") (10 3996.9838687783
2715.0867873303 0.0) (11 3804.6761764706 2715.0867873303 0.0))
((0 . "LINE") (100 . "AcDbEntity") (8 . "MASONRY") (62 . 7) (370 . 13) (100 . "AcDbLine") (10 3804.6761764706
2715.0867873303 0.0) (11 3793.363959276 2715.0867873303 0.0))
((0 . "LINE") (100 . "AcDbEntity") (8 . "MASONRY") (62 . 7) (370 . 13) (100 . "AcDbLine") (10 3795.2488687783
1739.5199095023 0.0) (11 3795.2488687783 1760.9360633484 0.0))
((0 . "LINE") (100 . "AcDbEntity") (8 . "MASONRY") (62 . 7) (370 . 13) (100 . "AcDbLine") (10 3802.7905769231
588.2415045249 0.0) (11 3793.363959276 588.2415045249 0.0))
((0 . "LINE") (100 . "AcDbEntity") (8 . "MASONRY") (62 . 7) (370 . 13) (100 . "AcDbLine") (10 3797.1337782805
2288.8383823529 0.0) (11 3797.1337782805 2320.8894343891 0.0))
((0 . "LINE") (100 . "AcDbEntity") (8 . "MASONRY") (62 . 7) (370 . 13) (100 . "AcDbLine") (10 3797.1337782805
2320.8894343891 0.0) (11 3981.9004524887 2320.8894343891 0.0))
((0 . "LINE") (100 . "AcDbEntity") (8 . "MASONRY") (62 . 7) (370 . 13) (100 . "AcDbLine") (10 3795.2488687783
1739.5199095023 0.0) (11 3917.7945475113 1739.5199095023 0.0))
((0 . "LINE") (100 . "AcDbEntity") (8 . "MASONRY") (62 . 7) (370 . 13) (100 . "AcDbLine") (10 3917.7945475113
1739.5199095023 0.0) (11 3917.7945475113 1711.9146153846 0.0))
((0 . "LINE") (100 . "AcDbEntity") (8 . "MASONRY") (62 . 7) (370 . 13) (100 . "AcDbLine") (10 3959.2760180995
2053.1674208145 0.0) (11 3800.3029072398 2053.1674208145 0.0))
((0 . "LINE") (100 . "AcDbEntity") (8 . "MASONRY") (62 . 7) (370 . 13) (100 . "AcDbLine") (10 3800.9049773756
1817.4971493213 0.0) (11 3800.9049773756 1828.8086764706 0.0))
((0 . "LINE") (100 . "AcDbEntity") (8 . "MASONRY") (62 . 7) (370 . 13) (100 . "AcDbLine") (10 3815.9883936652
1817.4971493213 0.0) (11 3800.9049773756 1817.4971493213 0.0))
((0 . "LINE") (100 . "AcDbEntity") (8 . "MASONRY") (62 . 7) (370 . 13) (100 . "AcDbLine") (10 3868.778280543
1670.4383257919 0.0) (11 3800.9049773756 1670.4383257919 0.0))
((0 . "LINE") (100 . "AcDbEntity") (8 . "MASONRY") (62 . 7) (370 . 13) (100 . "AcDbLine") (10 3802.7905769231
588.2415045249 0.0) (11 3965.569061086 588.2415045249 0.0))
((0 . "LINE") (100 . "AcDbEntity") (8 . "MASONRY") (62 . 7) (370 . 13) (100 . "AcDbLine") (10 3990.9476696833
596.155361991 0.0) (11 4004.5248868778 596.155361991 0.0))
((0 . "LINE") (100 . "AcDbEntity") (8 . "MASONRY") (62 . 7) (370 . 13) (100 . "AcDbLine") (10 3802.7905769231
588.2415045249 0.0) (11 3802.7905769231 599.5475113122 0.0))
((0 . "LINE") (100 . "AcDbEntity") (8 . "MASONRY") (62 . 7) (370 . 13) (100 . "AcDbLine") (10 3810.3315950226
3337.1040723982 0.0) (11 3810.3315950226 3310.7091289593 0.0))
((0 . "LINE") (100 . "AcDbEntity") (8 . "MASONRY") (62 . 7) (370 . 13) (100 . "AcDbLine") (10 3810.3315950226
3337.1040723982 0.0) (11 3981.9004524887 3337.1040723982 0.0))
((0 . "LINE") (100 . "AcDbEntity") (8 . "MASONRY") (62 . 7) (370 . 13) (100 . "AcDbLine") (10 3921.5681674208
2971.3419230769 0.0) (11 3812.2171945701 2971.3419230769 0.0))
((0 . "LINE") (100 . "AcDbEntity") (8 . "MASONRY") (62 . 7) (370 . 13) (100 . "AcDbLine") (10 3849.9250452489
2828.0542986425 0.0) (11 3819.7582126697 2828.0542986425 0.0))
((0 . "LINE") (100 . "AcDbEntity") (8 . "MASONRY") (62 . 7) (370 . 13) (100 . "AcDbLine") (10 3838.6128280543
2777.149321267 0.0) (11 3895.1739140271 2777.149321267 0.0))
((0 . "LINE") (100 . "AcDbEntity") (8 . "MASONRY") (62 . 7) (370 . 13) (100 . "AcDbLine") (10 3842.3826470588
2096.5306900452 0.0) (11 3914.0271493213 2096.5306900452 0.0))
((0 . "LINE") (100 . "AcDbEntity") (8 . "MASONRY") (62 . 7) (370 . 13) (100 . "AcDbLine") (10 4004.5248868778
1815.6108597285 0.0) (11 3842.3826470588 1815.6108597285 0.0))
((0 . "LINE") (100 . "AcDbEntity") (8 . "MASONRY") (62 . 7) (370 . 13) (100 . "AcDbLine") (10 3857.4660633484
1072.7757239819 0.0) (11 3929.1105656109 1072.7757239819 0.0))
((0 . "LINE") (100 . "AcDbEntity") (8 . "MASONRY") (62 . 7) (370 . 13) (100 . "AcDbLine") (10 3876.3192986425
773.0005882353 0.0) (11 3883.8616968326 773.0005882353 0.0))
((0 . "LINE") (100 . "AcDbEntity") (8 . "MASONRY") (62 . 7) (370 . 13) (100 . "AcDbLine") (10 3887.6315158371
859.7285067873 0.0) (11 3887.6315158371 840.8738914027 0.0))
((0 . "LINE") (100 . "AcDbEntity") (8 . "MASONRY") (62 . 7) (370 . 13) (100 . "AcDbLine") (10 3887.6315158371
859.7285067873 0.0) (11 3887.6315158371 938.9140271493 0.0))
((0 . "LINE") (100 . "AcDbEntity") (8 . "MASONRY") (62 . 7) (370 . 13) (100 . "AcDbLine") (10 3889.5171153846
805.1117081448 0.0) (11 3889.5171153846 829.5616742081 0.0))
((0 . "LINE") (100 . "AcDbEntity") (8 . "MASONRY") (62 . 7) (370 . 13) (100 . "AcDbLine") (10 3893.2883144796
1432.8817647059 0.0) (11 4049.7737556561 1432.8817647059 0.0))
((0 . "LINE") (100 . "AcDbEntity") (8 . "MASONRY") (62 . 7) (370 . 13) (100 . "AcDbLine") (10 3893.2883144796
1432.8817647059 0.0) (11 3893.2883144796 1466.8184162896 0.0))
((0 . "LINE") (100 . "AcDbEntity") (8 . "MASONRY") (62 . 7) (370 . 13) (100 . "AcDbLine") (10 4117.6470588235
805.1117081448 0.0) (11 3889.5171153846 805.1117081448 0.0))
((0 . "LINE") (100 . "AcDbEntity") (8 . "MASONRY") (62 . 7) (370 . 13) (100 . "AcDbLine") (10 3974.3594343891
1530.920520362 0.0) (11 3898.9437330317 1530.920520362 0.0))
((0 . "LINE") (100 . "AcDbEntity") (8 . "MASONRY") (62 . 7) (370 . 13) (100 . "AcDbLine") (10 3917.7983484163
1668.5520361991 0.0) (11 3906.4861312217 1668.5520361991 0.0))
((0 . "LINE") (100 . "AcDbEntity") (8 . "MASONRY") (62 . 7) (370 . 13) (100 . "AcDbLine") (10 3923.4544570136
2507.5417081448 0.0) (11 3923.4544570136 2473.6050565611 0.0))
((0 . "LINE") (100 . "AcDbEntity") (8 . "MASONRY") (62 . 7) (370 . 13) (100 . "AcDbLine") (10 3936.6515837104
3472.850678733 0.0) (11 3936.6515837104 3484.1628959276 0.0))
((0 . "LINE") (100 . "AcDbEntity") (8 . "MASONRY") (62 . 7) (370 . 13) (100 . "AcDbLine") (10 3936.6515837104
3472.850678733 0.0) (11 3981.9004524887 3472.850678733 0.0))
((0 . "LINE") (100 . "AcDbEntity") (8 . "MASONRY") (62 . 7) (370 . 13) (100 . "AcDbLine") (10 3951.7343099548
2779.0349208145 0.0) (11 3940.4227828054 2779.0349208145 0.0))
((0 . "LINE") (100 . "AcDbEntity") (8 . "MASONRY") (62 . 7) (370 . 13) (100 . "AcDbLine") (10 4004.5248868778
2779.0349208145 0.0) (11 3951.7343099548 2779.0349208145 0.0))
((0 . "LINE") (100 . "AcDbEntity") (8 . "MASONRY") (62 . 7) (370 . 13) (100 . "AcDbLine") (10 3951.7343099548
2779.0349208145 0.0) (11 3951.7343099548 2828.0542986425 0.0))
((0 . "LINE") (100 . "AcDbEntity") (8 . "MASONRY") (62 . 7) (370 . 13) (100 . "AcDbLine") (10 3953.6199095023
3318.2501470588 0.0) (11 3953.6199095023 3303.1674208145 0.0))
((0 . "LINE") (100 . "AcDbEntity") (8 . "MASONRY") (62 . 7) (370 . 13) (100 . "AcDbLine") (10 3955.5048190045
1657.2398190045 0.0) (11 4019.6083031674 1657.2398190045 0.0))
((0 . "LINE") (100 . "AcDbEntity") (8 . "MASONRY") (62 . 7) (370 . 13) (100 . "AcDbLine") (10 3959.2760180995
2053.1674208145 0.0) (11 3959.2760180995 1998.4919343891 0.0))
((0 . "LINE") (100 . "AcDbEntity") (8 . "MASONRY") (62 . 7) (370 . 13) (100 . "AcDbLine") (10 3959.2760180995
2053.1674208145 0.0) (11 3959.2760180995 2100.3018891403 0.0))
((0 . "LINE") (100 . "AcDbEntity") (8 . "MASONRY") (62 . 7) (370 . 13) (100 . "AcDbLine") (10 3959.2760180995
2100.3018891403 0.0) (11 3970.5882352941 2100.3018891403 0.0))
((0 . "LINE") (100 . "AcDbEntity") (8 . "MASONRY") (62 . 7) (370 . 13) (100 . "AcDbLine") (10 3970.5882352941
2100.3018891403 0.0) (11 4181.7491628959 2100.3018891403 0.0))
((0 . "LINE") (100 . "AcDbEntity") (8 . "MASONRY") (62 . 7) (370 . 13) (100 . "AcDbLine") (10 3983.7860520362
2520.7395248869 0.0) (11 3966.8170361991 2520.7395248869 0.0))
((0 . "LINE") (100 . "AcDbEntity") (8 . "MASONRY") (62 . 7) (370 . 13) (100 . "AcDbLine") (10 3966.8170361991
1742.0814479638 0.0) (11 4061.0859728507 1742.0814479638 0.0))
((0 . "LINE") (100 . "AcDbEntity") (8 . "MASONRY") (62 . 7) (370 . 13) (100 . "AcDbLine") (10 3970.5882352941
2976.9987217195 0.0) (11 3985.6716515837 2976.9987217195 0.0))
((0 . "LINE") (100 . "AcDbEntity") (8 . "MASONRY") (62 . 7) (370 . 13) (100 . "AcDbLine") (10 3981.9004524887
1238.6877828054 0.0) (11 3981.9004524887 1176.4705882353 0.0))
((0 . "LINE") (100 . "AcDbEntity") (8 . "MASONRY") (62 . 7) (370 . 13) (100 . "AcDbLine") (10 3981.9004524887
1568.6283710407 0.0) (11 3981.9004524887 1602.7120927602 0.0))
((0 . "LINE") (100 . "AcDbEntity") (8 . "MASONRY") (62 . 7) (370 . 13) (100 . "AcDbLine") (10 3983.7860520362
2673.4537669683 0.0) (11 3983.7860520362 2620.6638800905 0.0))
((0 . "LINE") (100 . "AcDbEntity") (8 . "MASONRY") (62 . 7) (370 . 13) (100 . "AcDbLine") (10 3983.7860520362
2520.7395248869 0.0) (11 3983.7860520362 2575.4150113122 0.0))
((0 . "LINE") (100 . "AcDbEntity") (8 . "MASONRY") (62 . 7) (370 . 13) (100 . "AcDbLine") (10 3981.9004524887
2320.8894343891 0.0) (11 3981.9004524887 2345.3994683258 0.0))
((0 . "LINE") (100 . "AcDbEntity") (8 . "MASONRY") (62 . 7) (370 . 13) (100 . "AcDbLine") (10 4206.2591968326
2320.8894343891 0.0) (11 3981.9004524887 2320.8894343891 0.0))
((0 . "LINE") (100 . "AcDbEntity") (8 . "MASONRY") (62 . 7) (370 . 13) (100 . "AcDbLine") (10 3981.9004524887
1238.6877828054 0.0) (11 3981.9004524887 1265.0088461538 0.0))
((0 . "LINE") (100 . "AcDbEntity") (8 . "MASONRY") (62 . 7) (370 . 13) (100 . "AcDbLine") (10 3981.9004524887
1265.0088461538 0.0) (11 3981.9004524887 1270.7381447964 0.0))
((0 . "LINE") (100 . "AcDbEntity") (8 . "MASONRY") (62 . 7) (370 . 13) (100 . "AcDbLine") (10 3981.9004524887
1238.6877828054 0.0) (11 4019.6083031674 1238.6877828054 0.0))
((0 . "LINE") (100 . "AcDbEntity") (8 . "MASONRY") (62 . 7) (370 . 13) (100 . "AcDbLine") (10 3983.7860520362
2520.7395248869 0.0) (11 4038.4615384615 2520.7395248869 0.0))
((0 . "LINE") (100 . "AcDbEntity") (8 . "MASONRY") (62 . 7) (370 . 13) (100 . "AcDbLine") (10 3985.6716515837
2375.5656108597 0.0) (11 3985.6716515837 2368.0239027149 0.0))
((0 . "LINE") (100 . "AcDbEntity") (8 . "MASONRY") (62 . 7) (370 . 13) (100 . "AcDbLine") (10 4098.7938235294
1602.7120927602 0.0) (11 3981.9004524887 1602.7120927602 0.0))
((0 . "LINE") (100 . "AcDbEntity") (8 . "MASONRY") (62 . 7) (370 . 13) (100 . "AcDbLine") (10 4012.0659049774
1304.6761764706 0.0) (11 3985.6716515837 1304.6761764706 0.0))
((0 . "LINE") (100 . "AcDbEntity") (8 . "MASONRY") (62 . 7) (370 . 13) (100 . "AcDbLine") (10 3996.9838687783
2473.6050565611 0.0) (11 3989.4414705882 2473.6050565611 0.0))
((0 . "LINE") (100 . "AcDbEntity") (8 . "MASONRY") (62 . 7) (370 . 13) (100 . "AcDbLine") (10 3996.9838687783
637.2539819005 0.0) (11 3996.9838687783 618.4021266968 0.0))
((0 . "LINE") (100 . "AcDbEntity") (8 . "MASONRY") (62 . 7) (370 . 13) (100 . "AcDbLine") (10 4061.0859728507
1964.5545927602 0.0) (11 4000.7536877828 1964.5545927602 0.0))
((0 . "LINE") (100 . "AcDbEntity") (8 . "MASONRY") (62 . 7) (370 . 13) (100 . "AcDbLine") (10 4117.6470588235
656.1085972851 0.0) (11 4008.2960859729 656.1085972851 0.0))
((0 . "LINE") (100 . "AcDbEntity") (8 . "MASONRY") (62 . 7) (370 . 13) (100 . "AcDbLine") (10 4027.149321267
2153.0917760181 0.0) (11 4019.6083031674 2153.0917760181 0.0))
((0 . "LINE") (100 . "AcDbEntity") (8 . "MASONRY") (62 . 7) (370 . 13) (100 . "AcDbLine") (10 4030.920520362
1240.5726923077 0.0) (11 4294.8713348416 1240.5726923077 0.0))
((0 . "LINE") (100 . "AcDbEntity") (8 . "MASONRY") (62 . 7) (370 . 13) (100 . "AcDbLine") (10 4034.6903393665
1336.7265384615 0.0) (11 4198.718178733 1336.7265384615 0.0))
((0 . "LINE") (100 . "AcDbEntity") (8 . "MASONRY") (62 . 7) (370 . 13) (100 . "AcDbLine") (10 4038.4615384615
2621.8680090498 0.0) (11 4407.8457466063 2621.8680090498 0.0))
((0 . "LINE") (100 . "AcDbEntity") (8 . "MASONRY") (62 . 7) (370 . 13) (100 . "AcDbLine") (10 4407.8457466063
2621.8680090498 0.0) (11 4419.3057239819 2621.8680090498 0.0))
((0 . "LINE") (100 . "AcDbEntity") (8 . "MASONRY") (62 . 7) (370 . 13) (100 . "AcDbLine") (10 4038.4615384615
2520.7395248869 0.0) (11 4415.5359049774 2520.7395248869 0.0))
((0 . "LINE") (100 . "AcDbEntity") (8 . "MASONRY") (62 . 7) (370 . 13) (100 . "AcDbLine") (10 4042.2327375566
1817.4957692308 0.0) (11 4051.6593552036 1817.4957692308 0.0))
((0 . "LINE") (100 . "AcDbEntity") (8 . "MASONRY") (62 . 7) (370 . 13) (100 . "AcDbLine") (10 4051.6593552036
1779.787918552 0.0) (11 4051.6593552036 1817.4957692308 0.0))
((0 . "LINE") (100 . "AcDbEntity") (8 . "MASONRY") (62 . 7) (370 . 13) (100 . "AcDbLine") (10 4117.6470588235
1817.4957692308 0.0) (11 4064.8571719457 1817.4957692308 0.0))
((0 . "LINE") (100 . "AcDbEntity") (8 . "MASONRY") (62 . 7) (370 . 13) (100 . "AcDbLine") (10 4064.8571719457
1817.4957692308 0.0) (11 4051.6593552036 1817.4957692308 0.0))
((0 . "LINE") (100 . "AcDbEntity") (8 . "MASONRY") (62 . 7) (370 . 13) (100 . "AcDbLine") (10 4095.0226244344
591.9291628959 0.0) (11 4057.3154638009 591.9291628959 0.0))
((0 . "LINE") (100 . "AcDbEntity") (8 . "MASONRY") (62 . 7) (370 . 13) (100 . "AcDbLine") (10 4057.3154638009
591.9291628959 0.0) (11 4057.3154638009 554.2986425339 0.0))
((0 . "LINE") (100 . "AcDbEntity") (8 . "MASONRY") (62 . 7) (370 . 13) (100 . "AcDbLine") (10 4061.0859728507
1964.5545927602 0.0) (11 4061.0859728507 1945.7013574661 0.0))
((0 . "LINE") (100 . "AcDbEntity") (8 . "MASONRY") (62 . 7) (370 . 13) (100 . "AcDbLine") (10 4061.0859728507
1964.5545927602 0.0) (11 4234.5404298643 1964.5545927602 0.0))
((0 . "LINE") (100 . "AcDbEntity") (8 . "MASONRY") (62 . 7) (370 . 13) (100 . "AcDbLine") (10 4087.4816063348
976.6218778281 0.0) (11 4072.3981900452 976.6218778281 0.0))
((0 . "LINE") (100 . "AcDbEntity") (8 . "MASONRY") (62 . 7) (370 . 13) (100 . "AcDbLine") (10 4076.1693891403
1743.9663574661 0.0) (11 4294.8713348416 1743.9663574661 0.0))
((0 . "LINE") (100 . "AcDbEntity") (8 . "MASONRY") (62 . 7) (370 . 13) (100 . "AcDbLine") (10 4151.5837104072
1470.5882352941 0.0) (11 4083.7104072398 1470.5882352941 0.0))
((0 . "LINE") (100 . "AcDbEntity") (8 . "MASONRY") (62 . 7) (370 . 13) (100 . "AcDbLine") (10 4087.4816063348
1647.8138914027 0.0) (11 4098.7938235294 1647.8138914027 0.0))
((0 . "LINE") (100 . "AcDbEntity") (8 . "MASONRY") (62 . 7) (370 . 13) (100 . "AcDbLine") (10 4098.7938235294
1602.7120927602 0.0) (11 4294.8713348416 1602.7120927602 0.0))
((0 . "LINE") (100 . "AcDbEntity") (8 . "MASONRY") (62 . 7) (370 . 13) (100 . "AcDbLine") (10 4098.7938235294
1602.7120927602 0.0) (11 4098.7938235294 1647.8138914027 0.0))
((0 . "LINE") (100 . "AcDbEntity") (8 . "MASONRY") (62 . 7) (370 . 13) (100 . "AcDbLine") (10 4087.4816063348
1425.3393665158 0.0) (11 4200.6037782805 1425.3393665158 0.0))
((0 . "LINE") (100 . "AcDbEntity") (8 . "MASONRY") (62 . 7) (370 . 13) (100 . "AcDbLine") (10 4096.9082239819
2198.3406447964 0.0) (11 4249.6262669683 2198.3406447964 0.0))
((0 . "LINE") (100 . "AcDbEntity") (8 . "MASONRY") (62 . 7) (370 . 13) (100 . "AcDbLine") (10 4096.9082239819
2198.3406447964 0.0) (11 4096.9082239819 2220.9650791855 0.0))
((0 . "LINE") (100 . "AcDbEntity") (8 . "MASONRY") (62 . 7) (370 . 13) (100 . "AcDbLine") (10 4106.334841629
595.7776923077 0.0) (11 4113.8758597285 595.7776923077 0.0))
((0 . "LINE") (100 . "AcDbEntity") (8 . "MASONRY") (62 . 7) (370 . 13) (100 . "AcDbLine") (10 4121.4182579186
1930.6186312217 0.0) (11 4110.106040724 1930.6186312217 0.0))
((0 . "LINE") (100 . "AcDbEntity") (8 . "MASONRY") (62 . 7) (370 . 13) (100 . "AcDbLine") (10 4098.7938235294
1647.8138914027 0.0) (11 4117.6470588235 1647.8138914027 0.0))
((0 . "LINE") (100 . "AcDbEntity") (8 . "MASONRY") (62 . 7) (370 . 13) (100 . "AcDbLine") (10 4121.4182579186
1885.3697624434 0.0) (11 4121.4182579186 1862.7453280543 0.0))
((0 . "LINE") (100 . "AcDbEntity") (8 . "MASONRY") (62 . 7) (370 . 13) (100 . "AcDbLine") (10 4134.6153846154
558.0684615385 0.0) (11 4134.6153846154 565.6108597285 0.0))
((0 . "LINE") (100 . "AcDbEntity") (8 . "MASONRY") (62 . 7) (370 . 13) (100 . "AcDbLine") (10 4152.5613800905 1075.8475
0.0) (11 4140.2714932127 1075.8475 0.0))
((0 . "LINE") (100 . "AcDbEntity") (8 . "MASONRY") (62 . 7) (370 . 13) (100 . "AcDbLine") (10 4149.6981108597
1123.679321267 0.0) (11 4149.6981108597 1112.3671040724 0.0))
((0 . "LINE") (100 . "AcDbEntity") (8 . "MASONRY") (62 . 7) (370 . 13) (100 . "AcDbLine") (10 4223.2282126697
2658.371040724 0.0) (11 4196.8325791855 2658.371040724 0.0))
((0 . "LINE") (100 . "AcDbEntity") (8 . "MASONRY") (62 . 7) (370 . 13) (100 . "AcDbLine") (10 4200.6037782805
1425.3393665158 0.0) (11 4200.6037782805 1401.3575226244 0.0))
((0 . "LINE") (100 . "AcDbEntity") (8 . "MASONRY") (62 . 7) (370 . 13) (100 . "AcDbLine") (10 4200.6037782805
1401.3575226244 0.0) (11 4294.8713348416 1401.3575226244 0.0))
((0 . "LINE") (100 . "AcDbEntity") (8 . "MASONRY") (62 . 7) (370 . 13) (100 . "AcDbLine") (10 4200.6037782805
1425.3393665158 0.0) (11 4200.6037782805 1436.6515837104 0.0))
((0 . "LINE") (100 . "AcDbEntity") (8 . "MASONRY") (62 . 7) (370 . 13) (100 . "AcDbLine") (10 4213.8009049774
1336.7265384615 0.0) (11 4198.718178733 1336.7265384615 0.0))
((0 . "LINE") (100 . "AcDbEntity") (8 . "MASONRY") (62 . 7) (370 . 13) (100 . "AcDbLine") (10 4198.718178733
1365.0084615385 0.0) (11 4198.718178733 1336.7265384615 0.0))
((0 . "LINE") (100 . "AcDbEntity") (8 . "MASONRY") (62 . 7) (370 . 13) (100 . "AcDbLine") (10 4200.6037782805
1472.4745248869 0.0) (11 4230.7692307692 1472.4745248869 0.0))
((0 . "LINE") (100 . "AcDbEntity") (8 . "MASONRY") (62 . 7) (370 . 13) (100 . "AcDbLine") (10 4206.2591968326
2320.8894343891 0.0) (11 4457.0135746606 2320.8894343891 0.0))
((0 . "LINE") (100 . "AcDbEntity") (8 . "MASONRY") (62 . 7) (370 . 13) (100 . "AcDbLine") (10 4206.2591968326
2320.8894343891 0.0) (11 4206.2591968326 2371.79510181 0.0))
((0 . "LINE") (100 . "AcDbEntity") (8 . "MASONRY") (62 . 7) (370 . 13) (100 . "AcDbLine") (10 4213.8009049774
1336.7265384615 0.0) (11 4213.8009049774 1293.3625791855 0.0))
((0 . "LINE") (100 . "AcDbEntity") (8 . "MASONRY") (62 . 7) (370 . 13) (100 . "AcDbLine") (10 4215.7631447964
2466.0633484163 0.0) (11 4215.7631447964 2410.0270022624 0.0))
((0 . "LINE") (100 . "AcDbEntity") (8 . "MASONRY") (62 . 7) (370 . 13) (100 . "AcDbLine") (10 4215.7631447964
2410.0270022624 0.0) (11 4460.7847737557 2410.0270022624 0.0))
((0 . "LINE") (100 . "AcDbEntity") (8 . "MASONRY") (62 . 7) (370 . 13) (100 . "AcDbLine") (10 4460.7847737557
2410.0270022624 0.0) (11 4460.7847737557 2386.8778280543 0.0))
((0 . "LINE") (100 . "AcDbEntity") (8 . "MASONRY") (62 . 7) (370 . 13) (100 . "AcDbLine") (10 4460.7847737557
2386.8778280543 0.0) (11 4460.7847737557 2371.79510181 0.0))
((0 . "LINE") (100 . "AcDbEntity") (8 . "MASONRY") (62 . 7) (370 . 13) (100 . "AcDbLine") (10 4215.6858144796
1826.9230769231 0.0) (11 4294.8713348416 1826.9230769231 0.0))
((0 . "LINE") (100 . "AcDbEntity") (8 . "MASONRY") (62 . 7) (370 . 13) (100 . "AcDbLine") (10 4213.8009049774
1336.7265384615 0.0) (11 4294.8713348416 1336.7265384615 0.0))
((0 . "LINE") (100 . "AcDbEntity") (8 . "MASONRY") (62 . 7) (370 . 13) (100 . "AcDbLine") (10 4223.2282126697
1700.60239819 0.0) (11 4223.2282126697 1685.520361991 0.0))
((0 . "LINE") (100 . "AcDbEntity") (8 . "MASONRY") (62 . 7) (370 . 13) (100 . "AcDbLine") (10 4298.6425339367
1657.2398190045 0.0) (11 4226.9980316742 1657.2398190045 0.0))
((0 . "LINE") (100 . "AcDbEntity") (8 . "MASONRY") (62 . 7) (370 . 13) (100 . "AcDbLine") (10 4230.7692307692
2113.4997058824 0.0) (11 4298.6425339367 2113.4997058824 0.0))
((0 . "LINE") (100 . "AcDbEntity") (8 . "MASONRY") (62 . 7) (370 . 13) (100 . "AcDbLine") (10 4234.5404298643
2026.7717873303 0.0) (11 4234.5404298643 1964.5545927602 0.0))
((0 . "LINE") (100 . "AcDbEntity") (8 . "MASONRY") (62 . 7) (370 . 13) (100 . "AcDbLine") (10 4234.5404298643
2066.3652375566 0.0) (11 4234.5404298643 2026.7717873303 0.0))
((0 . "LINE") (100 . "AcDbEntity") (8 . "MASONRY") (62 . 7) (370 . 13) (100 . "AcDbLine") (10 4294.8713348416
2026.7717873303 0.0) (11 4234.5404298643 2026.7717873303 0.0))
((0 . "LINE") (100 . "AcDbEntity") (8 . "MASONRY") (62 . 7) (370 . 13) (100 . "AcDbLine") (10 4294.8713348416
1964.5545927602 0.0) (11 4234.5404298643 1964.5545927602 0.0))
((0 . "LINE") (100 . "AcDbEntity") (8 . "MASONRY") (62 . 7) (370 . 13) (100 . "AcDbLine") (10 4298.6425339367
2198.3406447964 0.0) (11 4249.6262669683 2198.3406447964 0.0))
((0 . "LINE") (100 . "AcDbEntity") (8 . "MASONRY") (62 . 7) (370 . 13) (100 . "AcDbLine") (10 4298.6425339367
2225.4978393665 0.0) (11 4249.6262669683 2225.4978393665 0.0))
((0 . "LINE") (100 . "AcDbEntity") (8 . "MASONRY") (62 . 7) (370 . 13) (100 . "AcDbLine") (10 4249.6262669683
2225.4978393665 0.0) (11 4249.6262669683 2198.3406447964 0.0))
((0 . "LINE") (100 . "AcDbEntity") (8 . "MASONRY") (62 . 7) (370 . 13) (100 . "AcDbLine") (10 4294.8713348416
1466.8184162896 0.0) (11 4249.6224660633 1466.8184162896 0.0))
((0 . "LINE") (100 . "AcDbEntity") (8 . "MASONRY") (62 . 7) (370 . 13) (100 . "AcDbLine") (10 4260.9346832579
2662.1415497738 0.0) (11 4370.2870361991 2662.1415497738 0.0))
((0 . "LINE") (100 . "AcDbEntity") (8 . "MASONRY") (62 . 7) (370 . 13) (100 . "AcDbLine") (10 6541.2509276018
2205.8823529412 0.0) (11 6541.2509276018 2273.7556561086 0.0))
((0 . "LINE") (100 . "AcDbEntity") (8 . "MASONRY") (62 . 7) (370 . 13) (100 . "AcDbLine") (10 6541.2509276018
2273.7556561086 0.0) (11 6541.2509276018 2313.2738461538 0.0))
((0 . "LINE") (100 . "AcDbEntity") (8 . "MASONRY") (62 . 7) (370 . 13) (100 . "AcDbLine") (10 6541.2509276018
2313.2738461538 0.0) (11 6541.2509276018 2348.1142873303 0.0))
((0 . "LINE") (100 . "AcDbEntity") (8 . "MASONRY") (62 . 7) (370 . 13) (100 . "AcDbLine") (10 6541.2509276018
2348.1142873303 0.0) (11 6459.2760180995 2348.1142873303 0.0))
((0 . "LINE") (100 . "AcDbEntity") (8 . "MASONRY") (62 . 7) (370 . 13) (100 . "AcDbLine") (10 6459.2760180995
2348.1142873303 0.0) (11 6097.2850678733 2348.1142873303 0.0))
((0 . "LINE") (100 . "AcDbEntity") (8 . "MASONRY") (62 . 7) (370 . 13) (100 . "AcDbLine") (10 6097.2850678733
2348.1142873303 0.0) (11 5958.1149095023 2348.1142873303 0.0))
((0 . "LINE") (100 . "AcDbEntity") (8 . "MASONRY") (62 . 7) (370 . 13) (100 . "AcDbLine") (10 4912.9258144796
2348.1142873303 0.0) (11 4766.214638009 2348.1142873303 0.0))
((0 . "LINE") (100 . "AcDbEntity") (8 . "MASONRY") (62 . 7) (370 . 13) (100 . "AcDbLine") (10 4766.214638009
2348.1142873303 0.0) (11 4472.0969909502 2348.1142873303 0.0))
((0 . "LINE") (100 . "AcDbEntity") (8 . "MASONRY") (62 . 7) (370 . 13) (100 . "AcDbLine") (10 4472.0969909502
2348.1142873303 0.0) (11 4457.0135746606 2348.1142873303 0.0))
((0 . "LINE") (100 . "AcDbEntity") (8 . "MASONRY") (62 . 7) (370 . 13) (100 . "AcDbLine") (10 4457.0135746606
2348.1142873303 0.0) (11 4374.0568552036 2348.1142873303 0.0))
((0 . "LINE") (100 . "AcDbEntity") (8 . "MASONRY") (62 . 7) (370 . 13) (100 . "AcDbLine") (10 4374.0568552036
2348.1142873303 0.0) (11 4355.2550565611 2348.1142873303 0.0))
((0 . "LINE") (100 . "AcDbEntity") (8 . "MASONRY") (62 . 7) (370 . 13) (100 . "AcDbLine") (10 5015.0834162896
2665.9127488688 0.0) (11 4562.5947285068 2665.9127488688 0.0))
((0 . "LINE") (100 . "AcDbEntity") (8 . "MASONRY") (62 . 7) (370 . 13) (100 . "AcDbLine") (10 4562.5947285068
2665.9127488688 0.0) (11 4407.9935067873 2665.9127488688 0.0))
((0 . "LINE") (100 . "AcDbEntity") (8 . "MASONRY") (62 . 7) (370 . 13) (100 . "AcDbLine") (10 4607.8435972851
2575.414321267 0.0) (11 4419.3057239819 2575.414321267 0.0))
((0 . "LINE") (100 . "AcDbEntity") (8 . "MASONRY") (62 . 7) (370 . 13) (100 . "AcDbLine") (10 4457.0135746606
2349.1706674208 0.0) (11 4457.0135746606 2348.1142873303 0.0))
((0 . "LINE") (100 . "AcDbEntity") (8 . "MASONRY") (62 . 7) (370 . 13) (100 . "AcDbLine") (10 4457.0135746606
2348.1142873303 0.0) (11 4457.0135746606 2320.8894343891 0.0))
((0 . "LINE") (100 . "AcDbEntity") (8 . "MASONRY") (62 . 7) (370 . 13) (100 . "AcDbLine") (10 4528.6580769231
2320.8894343891 0.0) (11 4457.0135746606 2320.8894343891 0.0))
((0 . "LINE") (100 . "AcDbEntity") (8 . "MASONRY") (62 . 7) (370 . 13) (100 . "AcDbLine") (10 4464.5545927602
2439.6684049774 0.0) (11 4464.5545927602 2530.1661425339 0.0))
((0 . "LINE") (100 . "AcDbEntity") (8 . "MASONRY") (62 . 7) (370 . 13) (100 . "AcDbLine") (10 4464.5545927602
2631.9760972851 0.0) (11 4477.7524095023 2631.9760972851 0.0))
((0 . "LINE") (100 . "AcDbEntity") (8 . "MASONRY") (62 . 7) (370 . 13) (100 . "AcDbLine") (10 4464.5545927602
2549.0193778281 0.0) (11 4464.5545927602 2530.1661425339 0.0))
((0 . "LINE") (100 . "AcDbEntity") (8 . "MASONRY") (62 . 7) (370 . 13) (100 . "AcDbLine") (10 4973.6043665158
2530.1661425339 0.0) (11 4464.5545927602 2530.1661425339 0.0))
((0 . "LINE") (100 . "AcDbEntity") (8 . "MASONRY") (62 . 7) (370 . 13) (100 . "AcDbLine") (10 4477.7524095023
2631.9760972851 0.0) (11 4477.7524095023 2620.6638800905 0.0))
((0 . "LINE") (100 . "AcDbEntity") (8 . "MASONRY") (62 . 7) (370 . 13) (100 . "AcDbLine") (10 4477.7524095023
2631.9760972851 0.0) (11 4521.115678733 2631.9760972851 0.0))
((0 . "LINE") (100 . "AcDbEntity") (8 . "MASONRY") (62 . 7) (370 . 13) (100 . "AcDbLine") (10 4604.07239819
2633.8616968326 0.0) (11 4834.0879411765 2633.8616968326 0.0))
((0 . "LINE") (100 . "AcDbEntity") (8 . "MASONRY") (62 . 7) (370 . 13) (100 . "AcDbLine") (10 4607.8435972851
490.195158371 0.0) (11 4613.4990158371 490.195158371 0.0))
((0 . "LINE") (100 . "AcDbEntity") (8 . "MASONRY") (62 . 7) (370 . 13) (100 . "AcDbLine") (10 4613.4990158371
512.8195927602 0.0) (11 4613.4990158371 490.195158371 0.0))
((0 . "LINE") (100 . "AcDbEntity") (8 . "MASONRY") (62 . 7) (370 . 13) (100 . "AcDbLine") (10 4613.4990158371
490.195158371 0.0) (11 4622.9256334842 490.195158371 0.0))
((0 . "LINE") (100 . "AcDbEntity") (8 . "MASONRY") (62 . 7) (370 . 13) (100 . "AcDbLine") (10 4637.1328733032
467.5707239819 0.0) (11 4637.1328733032 454.7899321267 0.0))
((0 . "LINE") (100 . "AcDbEntity") (8 . "MASONRY") (62 . 7) (370 . 13) (100 . "AcDbLine") (10 4692.8436425339
2217.9706334842 0.0) (11 4653.9855542986 2217.9706334842 0.0))
((0 . "LINE") (100 . "AcDbEntity") (8 . "MASONRY") (62 . 7) (370 . 13) (100 . "AcDbLine") (10 4664.4046832579
514.7058823529 0.0) (11 4773.7556561086 514.7058823529 0.0))
((0 . "LINE") (100 . "AcDbEntity") (8 . "MASONRY") (62 . 7) (370 . 13) (100 . "AcDbLine") (10 4717.1945701357
2269.9851470588 0.0) (11 4705.8823529412 2269.9851470588 0.0))
((0 . "LINE") (100 . "AcDbEntity") (8 . "MASONRY") (62 . 7) (370 . 13) (100 . "AcDbLine") (10 4762.443438914
2292.609581448 0.0) (11 4777.5268552036 2292.609581448 0.0))
((0 . "LINE") (100 . "AcDbEntity") (8 . "MASONRY") (62 . 7) (370 . 13) (100 . "AcDbLine") (10 4792.6088914027
2305.80739819 0.0) (11 4807.6923076923 2305.80739819 0.0))
((0 . "LINE") (100 . "AcDbEntity") (8 . "MASONRY") (62 . 7) (370 . 13) (100 . "AcDbLine") (10 4819.0045248869
2579.185520362 0.0) (11 4834.0879411765 2579.185520362 0.0))
((0 . "LINE") (100 . "AcDbEntity") (8 . "MASONRY") (62 . 7) (370 . 13) (100 . "AcDbLine") (10 4834.0879411765
2579.185520362 0.0) (11 5009.4266176471 2579.185520362 0.0))
((0 . "LINE") (100 . "AcDbEntity") (8 . "MASONRY") (62 . 7) (370 . 13) (100 . "AcDbLine") (10 4822.7757239819
2317.1196153846 0.0) (11 4837.857760181 2317.1196153846 0.0))
((0 . "LINE") (100 . "AcDbEntity") (8 . "MASONRY") (62 . 7) (370 . 13) (100 . "AcDbLine") (10 4852.9411764706
2633.8616968326 0.0) (11 4996.228800905 2633.8616968326 0.0))
((0 . "LINE") (100 . "AcDbEntity") (8 . "MASONRY") (62 . 7) (370 . 13) (100 . "AcDbLine") (10 4856.7123755656
2329.1174434389 0.0) (11 4873.508540724 2329.1174434389 0.0))
((0 . "LINE") (100 . "AcDbEntity") (8 . "MASONRY") (62 . 7) (370 . 13) (100 . "AcDbLine") (10 5009.4266176471
2556.5610859729 0.0) (11 5009.4266176471 2579.185520362 0.0))
((0 . "LINE") (100 . "AcDbEntity") (8 . "MASONRY") (62 . 7) (370 . 13) (100 . "AcDbLine") (10 5009.4266176471
2579.185520362 0.0) (11 5018.8532352941 2579.185520362 0.0))
((0 . "LINE") (100 . "AcDbEntity") (8 . "MASONRY") (62 . 7) (370 . 13) (100 . "AcDbLine") (10 5678.7330316742
2526.3949434389 0.0) (11 5015.0834162896 2526.3949434389 0.0))
((0 . "LINE") (100 . "AcDbEntity") (8 . "MASONRY") (62 . 7) (370 . 13) (100 . "AcDbLine") (10 5018.8532352941
2594.2682466063 0.0) (11 5018.8532352941 2579.185520362 0.0))
((0 . "LINE") (100 . "AcDbEntity") (8 . "MASONRY") (62 . 7) (370 . 13) (100 . "AcDbLine") (10 5018.8532352941
2579.185520362 0.0) (11 5203.6199095023 2579.185520362 0.0))
((0 . "LINE") (100 . "AcDbEntity") (8 . "MASONRY") (62 . 7) (370 . 13) (100 . "AcDbLine") (10 5024.5100339367
2477.3755656109 0.0) (11 5024.5100339367 2492.4582918552 0.0))
((0 . "LINE") (100 . "AcDbEntity") (8 . "MASONRY") (62 . 7) (370 . 13) (100 . "AcDbLine") (10 5682.5042307692
2665.9127488688 0.0) (11 5026.3956334842 2665.9127488688 0.0))
((0 . "LINE") (100 . "AcDbEntity") (8 . "MASONRY") (62 . 7) (370 . 13) (100 . "AcDbLine") (10 5071.6445022624
2631.9760972851 0.0) (11 5026.3956334842 2631.9760972851 0.0))
((0 . "LINE") (100 . "AcDbEntity") (8 . "MASONRY") (62 . 7) (370 . 13) (100 . "AcDbLine") (10 5082.956719457
2631.9760972851 0.0) (11 5180.9954751131 2631.9760972851 0.0))
((0 . "LINE") (100 . "AcDbEntity") (8 . "MASONRY") (62 . 7) (370 . 13) (100 . "AcDbLine") (10 5092.1230429864
524.1318099548 0.0) (11 5092.1230429864 492.0500678733 0.0))
((0 . "LINE") (100 . "AcDbEntity") (8 . "MASONRY") (62 . 7) (370 . 13) (100 . "AcDbLine") (10 5290.3464479638
516.5921719457 0.0) (11 5154.599841629 516.5921719457 0.0))
((0 . "LINE") (100 . "AcDbEntity") (8 . "MASONRY") (62 . 7) (370 . 13) (100 . "AcDbLine") (10 5663.6496153846
2631.9760972851 0.0) (11 5207.3911085973 2631.9760972851 0.0))
((0 . "LINE") (100 . "AcDbEntity") (8 . "MASONRY") (62 . 7) (370 . 13) (100 . "AcDbLine") (10 5577.0611651584
516.5921719457 0.0) (11 5577.0611651584 505.3165497738 0.0))
((0 . "LINE") (100 . "AcDbEntity") (8 . "MASONRY") (62 . 7) (370 . 13) (100 . "AcDbLine") (10 5625.9431447964
516.5921719457 0.0) (11 5769.2307692308 516.5921719457 0.0))
((0 . "LINE") (100 . "AcDbEntity") (8 . "MASONRY") (62 . 7) (370 . 13) (100 . "AcDbLine") (10 5678.7330316742
2526.3949434389 0.0) (11 5678.7330316742 2560.3315950226 0.0))
((0 . "LINE") (100 . "AcDbEntity") (8 . "MASONRY") (62 . 7) (370 . 13) (100 . "AcDbLine") (10 5678.7330316742
2526.3949434389 0.0) (11 5940.7989366516 2526.3949434389 0.0))
((0 . "LINE") (100 . "AcDbEntity") (8 . "MASONRY") (62 . 7) (370 . 13) (100 . "AcDbLine") (10 5690.0452488688
2635.7466063348 0.0) (11 5682.5042307692 2635.7466063348 0.0))
((0 . "LINE") (100 . "AcDbEntity") (8 . "MASONRY") (62 . 7) (370 . 13) (100 . "AcDbLine") (10 5690.0452488688
2603.6948642534 0.0) (11 5682.5042307692 2603.6948642534 0.0))
((0 . "LINE") (100 . "AcDbEntity") (8 . "MASONRY") (62 . 7) (370 . 13) (100 . "AcDbLine") (10 5712.6696832579
2665.9127488688 0.0) (11 5697.5862669683 2665.9127488688 0.0))
((0 . "LINE") (100 . "AcDbEntity") (8 . "MASONRY") (62 . 7) (370 . 13) (100 . "AcDbLine") (10 5908.7478846154
2631.9760972851 0.0) (11 5814.4796380091 2631.9760972851 0.0))
((0 . "LINE") (100 . "AcDbEntity") (8 . "MASONRY") (62 . 7) (370 . 13) (100 . "AcDbLine") (10 5814.4796380091
2631.9760972851 0.0) (11 5739.0653167421 2631.9760972851 0.0))
((0 . "LINE") (100 . "AcDbEntity") (8 . "MASONRY") (62 . 7) (370 . 13) (100 . "AcDbLine") (10 5761.6897511312
2664.0271493213 0.0) (11 6119.9095022624 2664.0271493213 0.0))
((0 . "LINE") (100 . "AcDbEntity") (8 . "MASONRY") (62 . 7) (370 . 13) (100 . "AcDbLine") (10 6150.0756447964
2321.7897737557 0.0) (11 6011.8454411765 2321.7897737557 0.0))
((0 . "LINE") (100 . "AcDbEntity") (8 . "MASONRY") (62 . 7) (370 . 13) (100 . "AcDbLine") (10 5855.9579977376
508.9724434389 0.0) (11 5823.7840497738 508.9724434389 0.0))
((0 . "LINE") (100 . "AcDbEntity") (8 . "MASONRY") (62 . 7) (370 . 13) (100 . "AcDbLine") (10 5823.7840497738
508.9724434389 0.0) (11 5823.7840497738 483.2734049774 0.0))
((0 . "LINE") (100 . "AcDbEntity") (8 . "MASONRY") (62 . 7) (370 . 13) (100 . "AcDbLine") (10 5855.9579977376
500.8228280543 0.0) (11 5855.9579977376 508.9724434389 0.0))
((0 . "LINE") (100 . "AcDbEntity") (8 . "MASONRY") (62 . 7) (370 . 13) (100 . "AcDbLine") (10 5855.9579977376
520.3619909502 0.0) (11 5855.9579977376 508.9724434389 0.0))
((0 . "LINE") (100 . "AcDbEntity") (8 . "MASONRY") (62 . 7) (370 . 13) (100 . "AcDbLine") (10 6251.8855995475
2241.4263574661 0.0) (11 6145.3826470588 2241.4263574661 0.0))
((0 . "LINE") (100 . "AcDbEntity") (8 . "MASONRY") (62 . 7) (370 . 13) (100 . "AcDbLine") (10 5937.0284276018
2616.8926809955 0.0) (11 5937.0284276018 2633.8616968326 0.0))
((0 . "LINE") (100 . "AcDbEntity") (8 . "MASONRY") (62 . 7) (370 . 13) (100 . "AcDbLine") (10 5937.0284276018
2633.8616968326 0.0) (11 6425.3393665158 2633.8616968326 0.0))
((0 . "LINE") (100 . "AcDbEntity") (8 . "MASONRY") (62 . 7) (370 . 13) (100 . "AcDbLine") (10 5940.7989366516
2537.7071606335 0.0) (11 5940.7989366516 2526.3949434389 0.0))
((0 . "LINE") (100 . "AcDbEntity") (8 . "MASONRY") (62 . 7) (370 . 13) (100 . "AcDbLine") (10 6293.3632692308
2526.3949434389 0.0) (11 5940.7989366516 2526.3949434389 0.0))
((0 . "LINE") (100 . "AcDbEntity") (8 . "MASONRY") (62 . 7) (370 . 13) (100 . "AcDbLine") (10 6342.3833371041
2662.1415497738 0.0) (11 6131.221719457 2662.1415497738 0.0))
((0 . "LINE") (100 . "AcDbEntity") (8 . "MASONRY") (62 . 7) (370 . 13) (100 . "AcDbLine") (10 6161.387861991
516.5921719457 0.0) (11 6180.2410972851 516.5921719457 0.0))
((0 . "LINE") (100 . "AcDbEntity") (8 . "MASONRY") (62 . 7) (370 . 13) (100 . "AcDbLine") (10 6329.185520362
2398.1900452489 0.0) (11 6329.185520362 2385.0702488688 0.0))
((0 . "LINE") (100 . "AcDbEntity") (8 . "MASONRY") (62 . 7) (370 . 13) (100 . "AcDbLine") (10 6329.185520362
2385.0702488688 0.0) (11 6210.407239819 2385.0702488688 0.0))
((0 . "LINE") (100 . "AcDbEntity") (8 . "MASONRY") (62 . 7) (370 . 13) (100 . "AcDbLine") (10 6261.6691742081
483.788540724 0.0) (11 6261.6691742081 535.4440271493 0.0))
((0 . "LINE") (100 . "AcDbEntity") (8 . "MASONRY") (62 . 7) (370 . 13) (100 . "AcDbLine") (10 6263.1978167421
2573.5294117647 0.0) (11 6338.612138009 2573.5294117647 0.0))
((0 . "LINE") (100 . "AcDbEntity") (8 . "MASONRY") (62 . 7) (370 . 13) (100 . "AcDbLine") (10 6334.8416289593
2435.8972058824 0.0) (11 6334.8416289593 2443.4389140271 0.0))
((0 . "LINE") (100 . "AcDbEntity") (8 . "MASONRY") (62 . 7) (370 . 13) (100 . "AcDbLine") (10 6649.6981108597
2573.5294117647 0.0) (11 6338.612138009 2573.5294117647 0.0))
((0 . "LINE") (100 . "AcDbEntity") (8 . "MASONRY") (62 . 7) (370 . 13) (100 . "AcDbLine") (10 6852.7898303167
2498.037760181 0.0) (11 6647.8132013575 2498.037760181 0.0))
((0 . "LINE") (100 . "AcDbEntity") (8 . "MASONRY") (62 . 7) (370 . 13) (100 . "AcDbLine") (10 6647.8132013575
2498.037760181 0.0) (11 6647.8132013575 2473.7597171946 0.0))
((0 . "LINE") (100 . "AcDbEntity") (8 . "MASONRY") (62 . 7) (370 . 13) (100 . "AcDbLine") (10 6647.8132013575
2473.7597171946 0.0) (11 6338.612138009 2473.7597171946 0.0))
((0 . "LINE") (100 . "AcDbEntity") (8 . "MASONRY") (62 . 7) (370 . 13) (100 . "AcDbLine") (10 6338.612138009
2473.7597171946 0.0) (11 6338.612138009 2522.6244343891 0.0))
((0 . "LINE") (100 . "AcDbEntity") (8 . "MASONRY") (62 . 7) (370 . 13) (100 . "AcDbLine") (10 6338.612138009
2522.6244343891 0.0) (11 6338.612138009 2573.5294117647 0.0))
((0 . "LINE") (100 . "AcDbEntity") (8 . "MASONRY") (62 . 7) (370 . 13) (100 . "AcDbLine") (10 6500.7543778281
2386.8778280543 0.0) (11 6383.8610067873 2386.8778280543 0.0))
((0 . "LINE") (100 . "AcDbEntity") (8 . "MASONRY") (62 . 7) (370 . 13) (100 . "AcDbLine") (10 6527.149321267
2664.0271493213 0.0) (11 6402.7149321267 2664.0271493213 0.0))
((0 . "LINE") (100 . "AcDbEntity") (8 . "MASONRY") (62 . 7) (370 . 13) (100 . "AcDbLine") (10 6419.3449434389
531.6093099548 0.0) (11 6419.3449434389 565.6108597285 0.0))
((0 . "LINE") (100 . "AcDbEntity") (8 . "MASONRY") (62 . 7) (370 . 13) (100 . "AcDbLine") (10 6429.1098755656
2303.9211085973 0.0) (11 6512.0665950226 2303.9211085973 0.0))
((0 . "LINE") (100 . "AcDbEntity") (8 . "MASONRY") (62 . 7) (370 . 13) (100 . "AcDbLine") (10 6645.92760181
2635.7466063348 0.0) (11 6444.1932918552 2635.7466063348 0.0))
((0 . "LINE") (100 . "AcDbEntity") (8 . "MASONRY") (62 . 7) (370 . 13) (100 . "AcDbLine") (10 6527.149321267
2313.2738461538 0.0) (11 6541.2509276018 2313.2738461538 0.0))
((0 . "LINE") (100 . "AcDbEntity") (8 . "MASONRY") (62 . 7) (370 . 13) (100 . "AcDbLine") (10 6541.2509276018
2313.2738461538 0.0) (11 6568.6276809955 2313.2738461538 0.0))
((0 . "LINE") (100 . "AcDbEntity") (8 . "MASONRY") (62 . 7) (370 . 13) (100 . "AcDbLine") (10 6568.6276809955
2313.2738461538 0.0) (11 6602.5643325792 2313.2738461538 0.0))
((0 . "LINE") (100 . "AcDbEntity") (8 . "MASONRY") (62 . 7) (370 . 13) (100 . "AcDbLine") (10 6534.6910294118
2385.0702488688 0.0) (11 6770.358540724 2385.0702488688 0.0))
((0 . "LINE") (100 . "AcDbEntity") (8 . "MASONRY") (62 . 7) (370 . 13) (100 . "AcDbLine") (10 6770.358540724
2385.0702488688 0.0) (11 6770.358540724 2417.0439705882 0.0))
((0 . "LINE") (100 . "AcDbEntity") (8 . "MASONRY") (62 . 7) (370 . 13) (100 . "AcDbLine") (10 6602.5643325792
2273.7556561086 0.0) (11 6541.2509276018 2273.7556561086 0.0))
((0 . "LINE") (100 . "AcDbEntity") (8 . "MASONRY") (62 . 7) (370 . 13) (100 . "AcDbLine") (10 6541.2509276018
2273.7556561086 0.0) (11 6534.6910294118 2273.7556561086 0.0))
((0 . "LINE") (100 . "AcDbEntity") (8 . "MASONRY") (62 . 7) (370 . 13) (100 . "AcDbLine") (10 6677.9786538462
1134.9915384615 0.0) (11 6664.0938461538 1134.9915384615 0.0))
((0 . "LINE") (100 . "AcDbEntity") (8 . "MASONRY") (62 . 7) (370 . 13) (100 . "AcDbLine") (10 6664.0938461538
1134.9915384615 0.0) (11 6620.4972058824 1134.9915384615 0.0))
((0 . "LINE") (100 . "AcDbEntity") (8 . "MASONRY") (62 . 7) (370 . 13) (100 . "AcDbLine") (10 6549.7737556561
2337.8584502262 0.0) (11 6549.7737556561 2349.1706674208 0.0))
((0 . "LINE") (100 . "AcDbEntity") (8 . "MASONRY") (62 . 7) (370 . 13) (100 . "AcDbLine") (10 6595.0226244344
1155.0861877828 0.0) (11 6576.8287669683 1155.0861877828 0.0))
((0 . "LINE") (100 . "AcDbEntity") (8 . "MASONRY") (62 . 7) (370 . 13) (100 . "AcDbLine") (10 6602.5643325792
2273.7556561086 0.0) (11 6602.5643325792 2313.2738461538 0.0))
((0 . "LINE") (100 . "AcDbEntity") (8 . "MASONRY") (62 . 7) (370 . 13) (100 . "AcDbLine") (10 6602.5643325792
2313.2738461538 0.0) (11 6821.2635180995 2313.2738461538 0.0))
((0 . "LINE") (100 . "AcDbEntity") (8 . "MASONRY") (62 . 7) (370 . 13) (100 . "AcDbLine") (10 6821.2635180995
2313.2738461538 0.0) (11 6821.2635180995 2330.3167420814 0.0))
((0 . "LINE") (100 . "AcDbEntity") (8 . "MASONRY") (62 . 7) (370 . 13) (100 . "AcDbLine") (10 6783.5598076923
2273.7556561086 0.0) (11 6602.5643325792 2273.7556561086 0.0))
((0 . "LINE") (100 . "AcDbEntity") (8 . "MASONRY") (62 . 7) (370 . 13) (100 . "AcDbLine") (10 6687.4052714932
1907.9941968326 0.0) (11 6602.5643325792 1907.9941968326 0.0))
((0 . "LINE") (100 . "AcDbEntity") (8 . "MASONRY") (62 . 7) (370 . 13) (100 . "AcDbLine") (10 6689.2908710407
1672.3232352941 0.0) (11 6602.5643325792 1672.3232352941 0.0))
((0 . "LINE") (100 . "AcDbEntity") (8 . "MASONRY") (62 . 7) (370 . 13) (100 . "AcDbLine") (10 6606.334841629
2222.2486085973 0.0) (11 6642.1536425339 2222.2486085973 0.0))
((0 . "LINE") (100 . "AcDbEntity") (8 . "MASONRY") (62 . 7) (370 . 13) (100 . "AcDbLine") (10 6642.1536425339
2222.2486085973 0.0) (11 6642.1536425339 2202.1118438914 0.0))
((0 . "LINE") (100 . "AcDbEntity") (8 . "MASONRY") (62 . 7) (370 . 13) (100 . "AcDbLine") (10 6606.334841629
1742.0814479638 0.0) (11 6700.6065384615 1742.0814479638 0.0))
((0 . "LINE") (100 . "AcDbEntity") (8 . "MASONRY") (62 . 7) (370 . 13) (100 . "AcDbLine") (10 6606.334841629
1266.9683257919 0.0) (11 6647.8132013575 1266.9683257919 0.0))
((0 . "LINE") (100 . "AcDbEntity") (8 . "MASONRY") (62 . 7) (370 . 13) (100 . "AcDbLine") (10 6625.1887669683
1138.7627375566 0.0) (11 6606.334841629 1138.7627375566 0.0))
((0 . "LINE") (100 . "AcDbEntity") (8 . "MASONRY") (62 . 7) (370 . 13) (100 . "AcDbLine") (10 6610.1053506787
2104.07239819 0.0) (11 6651.5837104072 2104.07239819 0.0))
((0 . "LINE") (100 . "AcDbEntity") (8 . "MASONRY") (62 . 7) (370 . 13) (100 . "AcDbLine") (10 6875.9424547511
1987.1797171946 0.0) (11 6691.1025904977 1987.1797171946 0.0))
((0 . "LINE") (100 . "AcDbEntity") (8 . "MASONRY") (62 . 7) (370 . 13) (100 . "AcDbLine") (10 6691.1025904977
1987.1797171946 0.0) (11 6691.1025904977 2024.2875678733 0.0))
((0 . "LINE") (100 . "AcDbEntity") (8 . "MASONRY") (62 . 7) (370 . 13) (100 . "AcDbLine") (10 6691.1025904977
2024.2875678733 0.0) (11 6610.1053506787 2024.2875678733 0.0))
((0 . "LINE") (100 . "AcDbEntity") (8 . "MASONRY") (62 . 7) (370 . 13) (100 . "AcDbLine") (10 6700.6030882353
1432.8817647059 0.0) (11 6610.1053506787 1432.8817647059 0.0))
((0 . "LINE") (100 . "AcDbEntity") (8 . "MASONRY") (62 . 7) (370 . 13) (100 . "AcDbLine") (10 6783.5598076923
1336.7265384615 0.0) (11 6610.1053506787 1336.7265384615 0.0))
((0 . "LINE") (100 . "AcDbEntity") (8 . "MASONRY") (62 . 7) (370 . 13) (100 . "AcDbLine") (10 6628.8370701357
531.6141402715 0.0) (11 6644.0420022624 531.6141402715 0.0))
((0 . "LINE") (100 . "AcDbEntity") (8 . "MASONRY") (62 . 7) (370 . 13) (100 . "AcDbLine") (10 6645.92760181
2635.7466063348 0.0) (11 6645.92760181 2662.1415497738 0.0))
((0 . "LINE") (100 . "AcDbEntity") (8 . "MASONRY") (62 . 7) (370 . 13) (100 . "AcDbLine") (10 6649.6981108597
2573.5294117647 0.0) (11 6649.6981108597 2533.9366515837 0.0))
((0 . "LINE") (100 . "AcDbEntity") (8 . "MASONRY") (62 . 7) (370 . 13) (100 . "AcDbLine") (10 6649.6981108597
2573.5294117647 0.0) (11 6794.8720248869 2573.5294117647 0.0))
((0 . "LINE") (100 . "AcDbEntity") (8 . "MASONRY") (62 . 7) (370 . 13) (100 . "AcDbLine") (10 6644.0420022624
1591.2528054299 0.0) (11 6644.0420022624 1583.7104072398 0.0))
((0 . "LINE") (100 . "AcDbEntity") (8 . "MASONRY") (62 . 7) (370 . 13) (100 . "AcDbLine") (10 6645.92760181
2635.7466063348 0.0) (11 6907.9941968326 2635.7466063348 0.0))
((0 . "LINE") (100 . "AcDbEntity") (8 . "MASONRY") (62 . 7) (370 . 13) (100 . "AcDbLine") (10 6651.5837104072
2115.3846153846 0.0) (11 6651.5837104072 2104.07239819 0.0))
((0 . "LINE") (100 . "AcDbEntity") (8 . "MASONRY") (62 . 7) (370 . 13) (100 . "AcDbLine") (10 6659.125418552
2104.07239819 0.0) (11 6651.5837104072 2104.07239819 0.0))
((0 . "LINE") (100 . "AcDbEntity") (8 . "MASONRY") (62 . 7) (370 . 13) (100 . "AcDbLine") (10 6659.125418552
2156.8629751131 0.0) (11 6815.6108597285 2156.8629751131 0.0))
((0 . "LINE") (100 . "AcDbEntity") (8 . "MASONRY") (62 . 7) (370 . 13) (100 . "AcDbLine") (10 6700.6030882353
1291.4790497738 0.0) (11 6666.6664366516 1291.4790497738 0.0))
((0 . "LINE") (100 . "AcDbEntity") (8 . "MASONRY") (62 . 7) (370 . 13) (100 . "AcDbLine") (10 6670.4376357466
1257.467138009 0.0) (11 7023.0019683258 1257.467138009 0.0))
((0 . "LINE") (100 . "AcDbEntity") (8 . "MASONRY") (62 . 7) (370 . 13) (100 . "AcDbLine") (10 6687.4052714932
1900.4524886878 0.0) (11 6687.4052714932 1907.9941968326 0.0))
((0 . "LINE") (100 . "AcDbEntity") (8 . "MASONRY") (62 . 7) (370 . 13) (100 . "AcDbLine") (10 6687.4052714932
1907.9941968326 0.0) (11 6813.725260181 1907.9941968326 0.0))
((0 . "LINE") (100 . "AcDbEntity") (8 . "MASONRY") (62 . 7) (370 . 13) (100 . "AcDbLine") (10 6691.1764705882
1877.8280542986 0.0) (11 6691.1764705882 1858.9741289593 0.0))
((0 . "LINE") (100 . "AcDbEntity") (8 . "MASONRY") (62 . 7) (370 . 13) (100 . "AcDbLine") (10 6694.946979638
1553.5435746606 0.0) (11 6694.946979638 1572.3981900452 0.0))
((0 . "LINE") (100 . "AcDbEntity") (8 . "MASONRY") (62 . 7) (370 . 13) (100 . "AcDbLine") (10 6832.5791855204
727.7496493213 0.0) (11 6742.0814479638 727.7496493213 0.0))
((0 . "LINE") (100 . "AcDbEntity") (8 . "MASONRY") (62 . 7) (370 . 13) (100 . "AcDbLine") (10 6700.6065384615
1742.0814479638 0.0) (11 6836.3496945701 1742.0814479638 0.0))
((0 . "LINE") (100 . "AcDbEntity") (8 . "MASONRY") (62 . 7) (370 . 13) (100 . "AcDbLine") (10 6868.4007466063
1813.7245701357 0.0) (11 6700.6065384615 1813.7245701357 0.0))
((0 . "LINE") (100 . "AcDbEntity") (8 . "MASONRY") (62 . 7) (370 . 13) (100 . "AcDbLine") (10 6700.6065384615
1813.7245701357 0.0) (11 6700.6065384615 1742.0814479638 0.0))
((0 . "LINE") (100 . "AcDbEntity") (8 . "MASONRY") (62 . 7) (370 . 13) (100 . "AcDbLine") (10 6700.6030882353
1538.387658371 0.0) (11 6836.3496945701 1538.387658371 0.0))
((0 . "LINE") (100 . "AcDbEntity") (8 . "MASONRY") (62 . 7) (370 . 13) (100 . "AcDbLine") (10 6836.3496945701
1538.387658371 0.0) (11 6862.7453280543 1538.387658371 0.0))
((0 . "LINE") (100 . "AcDbEntity") (8 . "MASONRY") (62 . 7) (370 . 13) (100 . "AcDbLine") (10 6862.7453280543
1538.387658371 0.0) (11 7028.6573868778 1538.387658371 0.0))
((0 . "LINE") (100 . "AcDbEntity") (8 . "MASONRY") (62 . 7) (370 . 13) (100 . "AcDbLine") (10 6700.6030882353
1432.8817647059 0.0) (11 6700.6030882353 1459.2760180995 0.0))
((0 . "LINE") (100 . "AcDbEntity") (8 . "MASONRY") (62 . 7) (370 . 13) (100 . "AcDbLine") (10 6700.6030882353
1432.8817647059 0.0) (11 6821.2669683258 1432.8817647059 0.0))
((0 . "LINE") (100 . "AcDbEntity") (8 . "MASONRY") (62 . 7) (370 . 13) (100 . "AcDbLine") (10 6704.3742873303
2104.07239819 0.0) (11 6772.2475904977 2104.07239819 0.0))
((0 . "LINE") (100 . "AcDbEntity") (8 . "MASONRY") (62 . 7) (370 . 13) (100 . "AcDbLine") (10 6779.7886085973
1031.2980542986 0.0) (11 6708.1447963801 1031.2980542986 0.0))
((0 . "LINE") (100 . "AcDbEntity") (8 . "MASONRY") (62 . 7) (370 . 13) (100 . "AcDbLine") (10 6832.5791855204
835.2191628959 0.0) (11 6742.0814479638 835.2191628959 0.0))
((0 . "LINE") (100 . "AcDbEntity") (8 . "MASONRY") (62 . 7) (370 . 13) (100 . "AcDbLine") (10 6826.9230769231
1093.437918552 0.0) (11 6734.539739819 1093.437918552 0.0))
((0 . "LINE") (100 . "AcDbEntity") (8 . "MASONRY") (62 . 7) (370 . 13) (100 . "AcDbLine") (10 6734.539739819
1093.437918552 0.0) (11 6719.4570135747 1093.437918552 0.0))
((0 . "LINE") (100 . "AcDbEntity") (8 . "MASONRY") (62 . 7) (370 . 13) (100 . "AcDbLine") (10 6819.3820588235
1165.1583710407 0.0) (11 6730.7692307692 1165.1583710407 0.0))
((0 . "LINE") (100 . "AcDbEntity") (8 . "MASONRY") (62 . 7) (370 . 13) (100 . "AcDbLine") (10 6855.2036199095
776.7635067873 0.0) (11 6742.0814479638 776.7635067873 0.0))
((0 . "LINE") (100 . "AcDbEntity") (8 . "MASONRY") (62 . 7) (370 . 13) (100 . "AcDbLine") (10 6853.4664705882
2786.575938914 0.0) (11 6853.4664705882 2757.1471945701 0.0))
((0 . "LINE") (100 . "AcDbEntity") (8 . "MASONRY") (62 . 7) (370 . 13) (100 . "AcDbLine") (10 6853.4664705882
2757.1471945701 0.0) (11 6821.2669683258 2757.1471945701 0.0))
((0 . "LINE") (100 . "AcDbEntity") (8 . "MASONRY") (62 . 7) (370 . 13) (100 . "AcDbLine") (10 6772.853800905
465.0953959276 0.0) (11 6772.853800905 484.5728846154 0.0))
((0 . "LINE") (100 . "AcDbEntity") (8 . "MASONRY") (62 . 7) (370 . 13) (100 . "AcDbLine") (10 6772.853800905
484.5728846154 0.0) (11 6738.60989819 484.5728846154 0.0))
((0 . "LINE") (100 . "AcDbEntity") (8 . "MASONRY") (62 . 7) (370 . 13) (100 . "AcDbLine") (10 6815.5335294118
1334.8416289593 0.0) (11 6815.5335294118 1367.343540724 0.0))
((0 . "LINE") (100 . "AcDbEntity") (8 . "MASONRY") (62 . 7) (370 . 13) (100 . "AcDbLine") (10 6815.5335294118
1367.343540724 0.0) (11 6751.5080656109 1367.343540724 0.0))
((0 . "LINE") (100 . "AcDbEntity") (8 . "MASONRY") (62 . 7) (370 . 13) (100 . "AcDbLine") (10 6751.5080656109
1367.343540724 0.0) (11 6751.5080656109 1395.1725339367 0.0))
((0 . "LINE") (100 . "AcDbEntity") (8 . "MASONRY") (62 . 7) (370 . 13) (100 . "AcDbLine") (10 6753.3936651584
1670.4383257919 0.0) (11 6783.5598076923 1670.4383257919 0.0))
((0 . "LINE") (100 . "AcDbEntity") (8 . "MASONRY") (62 . 7) (370 . 13) (100 . "AcDbLine") (10 6753.3936651584
1466.8184162896 0.0) (11 6772.2475904977 1466.8184162896 0.0))
((0 . "LINE") (100 . "AcDbEntity") (8 . "MASONRY") (62 . 7) (370 . 13) (100 . "AcDbLine") (10 6760.9353733032
599.5475113122 0.0) (11 6760.9353733032 539.2166063348 0.0))
((0 . "LINE") (100 . "AcDbEntity") (8 . "MASONRY") (62 . 7) (370 . 13) (100 . "AcDbLine") (10 6866.5158371041
2818.701561086 0.0) (11 6821.2669683258 2818.701561086 0.0))
((0 . "LINE") (100 . "AcDbEntity") (8 . "MASONRY") (62 . 7) (370 . 13) (100 . "AcDbLine") (10 6826.9230769231
1025.6419457014 0.0) (11 6802.4130429864 1025.6419457014 0.0))
((0 . "LINE") (100 . "AcDbEntity") (8 . "MASONRY") (62 . 7) (370 . 13) (100 . "AcDbLine") (10 7139.893959276
2271.8707466063 0.0) (11 6960.7840837104 2271.8707466063 0.0))
((0 . "LINE") (100 . "AcDbEntity") (8 . "MASONRY") (62 . 7) (370 . 13) (100 . "AcDbLine") (10 6960.7840837104
2271.8707466063 0.0) (11 6809.9547511312 2271.8707466063 0.0))
((0 . "LINE") (100 . "AcDbEntity") (8 . "MASONRY") (62 . 7) (370 . 13) (100 . "AcDbLine") (10 6815.6108597285
2156.8629751131 0.0) (11 6815.6108597285 2111.6141063348 0.0))
((0 . "LINE") (100 . "AcDbEntity") (8 . "MASONRY") (62 . 7) (370 . 13) (100 . "AcDbLine") (10 6815.6108597285
2156.8629751131 0.0) (11 7015.460260181 2156.8629751131 0.0))
((0 . "LINE") (100 . "AcDbEntity") (8 . "MASONRY") (62 . 7) (370 . 13) (100 . "AcDbLine") (10 7015.460260181
2156.8629751131 0.0) (11 7015.460260181 2188.9140271493 0.0))
((0 . "LINE") (100 . "AcDbEntity") (8 . "MASONRY") (62 . 7) (370 . 13) (100 . "AcDbLine") (10 6821.2669683258
1466.8184162896 0.0) (11 6821.2669683258 1432.8817647059 0.0))
((0 . "LINE") (100 . "AcDbEntity") (8 . "MASONRY") (62 . 7) (370 . 13) (100 . "AcDbLine") (10 6819.3820588235
1146.3037556561 0.0) (11 6819.3820588235 1165.1583710407 0.0))
((0 . "LINE") (100 . "AcDbEntity") (8 . "MASONRY") (62 . 7) (370 . 13) (100 . "AcDbLine") (10 6950.0739366516
1165.1583710407 0.0) (11 6819.3820588235 1165.1583710407 0.0))
((0 . "LINE") (100 . "AcDbEntity") (8 . "MASONRY") (62 . 7) (370 . 13) (100 . "AcDbLine") (10 6983.4085180995
3184.3891402715 0.0) (11 6821.2669683258 3184.3891402715 0.0))
((0 . "LINE") (100 . "AcDbEntity") (8 . "MASONRY") (62 . 7) (370 . 13) (100 . "AcDbLine") (10 6821.2669683258
3114.6302375566 0.0) (11 6885.3697624434 3114.6302375566 0.0))
((0 . "LINE") (100 . "AcDbEntity") (8 . "MASONRY") (62 . 7) (370 . 13) (100 . "AcDbLine") (10 6821.2669683258
1410.2573303167 0.0) (11 6821.2669683258 1432.8817647059 0.0))
((0 . "LINE") (100 . "AcDbEntity") (8 . "MASONRY") (62 . 7) (370 . 13) (100 . "AcDbLine") (10 6821.2669683258
584.4654751131 0.0) (11 6945.7013574661 584.4654751131 0.0))
((0 . "LINE") (100 . "AcDbEntity") (8 . "MASONRY") (62 . 7) (370 . 13) (100 . "AcDbLine") (10 6825.0374773756
2899.8113461538 0.0) (11 6857.1175226244 2899.8113461538 0.0))
((0 . "LINE") (100 . "AcDbEntity") (8 . "MASONRY") (62 . 7) (370 . 13) (100 . "AcDbLine") (10 6857.1175226244
2899.8113461538 0.0) (11 6857.1175226244 2907.2398190045 0.0))
((0 . "LINE") (100 . "AcDbEntity") (8 . "MASONRY") (62 . 7) (370 . 13) (100 . "AcDbLine") (10 6830.6935859729
2345.3994683258 0.0) (11 6830.6935859729 2424.5849886878 0.0))
((0 . "LINE") (100 . "AcDbEntity") (8 . "MASONRY") (62 . 7) (370 . 13) (100 . "AcDbLine") (10 6826.9230769231
1025.6419457014 0.0) (11 6826.9230769231 1093.437918552 0.0))
((0 . "LINE") (100 . "AcDbEntity") (8 . "MASONRY") (62 . 7) (370 . 13) (100 . "AcDbLine") (10 6826.9230769231
1093.437918552 0.0) (11 6911.7647058824 1093.437918552 0.0))
((0 . "LINE") (100 . "AcDbEntity") (8 . "MASONRY") (62 . 7) (370 . 13) (100 . "AcDbLine") (10 7209.652861991
2973.2282126697 0.0) (11 6828.8086764706 2973.2282126697 0.0))
((0 . "LINE") (100 . "AcDbEntity") (8 . "MASONRY") (62 . 7) (370 . 13) (100 . "AcDbLine") (10 6826.9230769231
1025.6419457014 0.0) (11 6836.3496945701 1025.6419457014 0.0))
((0 . "LINE") (100 . "AcDbEntity") (8 . "MASONRY") (62 . 7) (370 . 13) (100 . "AcDbLine") (10 6832.5791855204
2471.7967873303 0.0) (11 6852.7898303167 2471.7967873303 0.0))
((0 . "LINE") (100 . "AcDbEntity") (8 . "MASONRY") (62 . 7) (370 . 13) (100 . "AcDbLine") (10 6852.7898303167
2471.7967873303 0.0) (11 6852.7898303167 2498.037760181 0.0))
((0 . "LINE") (100 . "AcDbEntity") (8 . "MASONRY") (62 . 7) (370 . 13) (100 . "AcDbLine") (10 6834.4640950226
965.308280543 0.0) (11 6834.4640950226 984.1628959276 0.0))
((0 . "LINE") (100 . "AcDbEntity") (8 . "MASONRY") (62 . 7) (370 . 13) (100 . "AcDbLine") (10 6832.5791855204
863.4983257919 0.0) (11 6832.5791855204 835.2191628959 0.0))
((0 . "LINE") (100 . "AcDbEntity") (8 . "MASONRY") (62 . 7) (370 . 13) (100 . "AcDbLine") (10 6832.5791855204
835.2191628959 0.0) (11 7036.5677941176 835.2191628959 0.0))
((0 . "LINE") (100 . "AcDbEntity") (8 . "MASONRY") (62 . 7) (370 . 13) (100 . "AcDbLine") (10 6832.5791855204
727.7496493213 0.0) (11 6832.5791855204 686.2754298643 0.0))
((0 . "LINE") (100 . "AcDbEntity") (8 . "MASONRY") (62 . 7) (370 . 13) (100 . "AcDbLine") (10 6832.5791855204
727.7496493213 0.0) (11 6907.9941968326 727.7496493213 0.0))
((0 . "LINE") (100 . "AcDbEntity") (8 . "MASONRY") (62 . 7) (370 . 13) (100 . "AcDbLine") (10 6836.3496945701
1776.0180995475 0.0) (11 6836.3496945701 1742.0814479638 0.0))
((0 . "LINE") (100 . "AcDbEntity") (8 . "MASONRY") (62 . 7) (370 . 13) (100 . "AcDbLine") (10 7024.8868778281
1742.0814479638 0.0) (11 6885.3697624434 1742.0814479638 0.0))
((0 . "LINE") (100 . "AcDbEntity") (8 . "MASONRY") (62 . 7) (370 . 13) (100 . "AcDbLine") (10 6885.3697624434
1742.0814479638 0.0) (11 6836.3496945701 1742.0814479638 0.0))
((0 . "LINE") (100 . "AcDbEntity") (8 . "MASONRY") (62 . 7) (370 . 13) (100 . "AcDbLine") (10 6847.6619117647
3525.6412556561 0.0) (11 6972.096300905 3525.6412556561 0.0))
((0 . "LINE") (100 . "AcDbEntity") (8 . "MASONRY") (62 . 7) (370 . 13) (100 . "AcDbLine") (10 7175.7162104072
3257.9185520362 0.0) (11 6847.6619117647 3257.9185520362 0.0))
((0 . "LINE") (100 . "AcDbEntity") (8 . "MASONRY") (62 . 7) (370 . 13) (100 . "AcDbLine") (10 6853.3187104072
3427.6018099548 0.0) (11 6853.3187104072 3382.3529411765 0.0))
((0 . "LINE") (100 . "AcDbEntity") (8 . "MASONRY") (62 . 7) (370 . 13) (100 . "AcDbLine") (10 6857.0926696833
3450.2262443439 0.0) (11 6857.0926696833 3470.9657692308 0.0))
((0 . "LINE") (100 . "AcDbEntity") (8 . "MASONRY") (62 . 7) (370 . 13) (100 . "AcDbLine") (10 6857.0926696833
3470.9657692308 0.0) (11 6972.096300905 3470.9657692308 0.0))
((0 . "LINE") (100 . "AcDbEntity") (8 . "MASONRY") (62 . 7) (370 . 13) (100 . "AcDbLine") (10 6852.7898303167
2498.037760181 0.0) (11 7149.3212669683 2498.037760181 0.0))
((0 . "LINE") (100 . "AcDbEntity") (8 . "MASONRY") (62 . 7) (370 . 13) (100 . "AcDbLine") (10 7149.3212669683
2498.037760181 0.0) (11 7228.5067873303 2498.037760181 0.0))
((0 . "LINE") (100 . "AcDbEntity") (8 . "MASONRY") (62 . 7) (370 . 13) (100 . "AcDbLine") (10 6945.7013574661
3341.0292420814 0.0) (11 6870.2863461538 3341.0292420814 0.0))
((0 . "LINE") (100 . "AcDbEntity") (8 . "MASONRY") (62 . 7) (370 . 13) (100 . "AcDbLine") (10 6870.2863461538
3341.0292420814 0.0) (11 6858.9741289593 3341.0292420814 0.0))
((0 . "LINE") (100 . "AcDbEntity") (8 . "MASONRY") (62 . 7) (370 . 13) (100 . "AcDbLine") (10 6862.7453280543
1674.1308144796 0.0) (11 6877.8280542986 1674.1308144796 0.0))
((0 . "LINE") (100 . "AcDbEntity") (8 . "MASONRY") (62 . 7) (370 . 13) (100 . "AcDbLine") (10 6877.8280542986
1674.1308144796 0.0) (11 7017.3451696833 1674.1308144796 0.0))
((0 . "LINE") (100 . "AcDbEntity") (8 . "MASONRY") (62 . 7) (370 . 13) (100 . "AcDbLine") (10 6866.5158371041
2818.701561086 0.0) (11 6866.5158371041 2865.761459276 0.0))
((0 . "LINE") (100 . "AcDbEntity") (8 . "MASONRY") (62 . 7) (370 . 13) (100 . "AcDbLine") (10 6866.5158371041
2818.701561086 0.0) (11 7175.7162104072 2818.701561086 0.0))
((0 . "LINE") (100 . "AcDbEntity") (8 . "MASONRY") (62 . 7) (370 . 13) (100 . "AcDbLine") (10 7175.7162104072
2818.701561086 0.0) (11 7213.346040724 2818.701561086 0.0))
((0 . "LINE") (100 . "AcDbEntity") (8 . "MASONRY") (62 . 7) (370 . 13) (100 . "AcDbLine") (10 7213.346040724
2818.701561086 0.0) (11 7213.346040724 2865.761459276 0.0))
((0 . "LINE") (100 . "AcDbEntity") (8 . "MASONRY") (62 . 7) (370 . 13) (100 . "AcDbLine") (10 6896.681979638
1813.7245701357 0.0) (11 6868.4007466063 1813.7245701357 0.0))
((0 . "LINE") (100 . "AcDbEntity") (8 . "MASONRY") (62 . 7) (370 . 13) (100 . "AcDbLine") (10 6868.4007466063
1828.8086764706 0.0) (11 6868.4007466063 1813.7245701357 0.0))
((0 . "LINE") (100 . "AcDbEntity") (8 . "MASONRY") (62 . 7) (370 . 13) (100 . "AcDbLine") (10 7038.0840045249
1334.8416289593 0.0) (11 6866.5158371041 1334.8416289593 0.0))
((0 . "LINE") (100 . "AcDbEntity") (8 . "MASONRY") (62 . 7) (370 . 13) (100 . "AcDbLine") (10 6875.9424547511
1987.1797171946 0.0) (11 7013.5746606335 1987.1797171946 0.0))
((0 . "LINE") (100 . "AcDbEntity") (8 . "MASONRY") (62 . 7) (370 . 13) (100 . "AcDbLine") (10 6875.9424547511
1987.1797171946 0.0) (11 6875.9424547511 2021.0390384615 0.0))
((0 . "LINE") (100 . "AcDbEntity") (8 . "MASONRY") (62 . 7) (370 . 13) (100 . "AcDbLine") (10 6875.9424547511
2021.0390384615 0.0) (11 7013.5746606335 2021.0390384615 0.0))
((0 . "LINE") (100 . "AcDbEntity") (8 . "MASONRY") (62 . 7) (370 . 13) (100 . "AcDbLine") (10 6923.0769230769
1921.1878733032 0.0) (11 6870.8145361991 1921.1878733032 0.0))
((0 . "LINE") (100 . "AcDbEntity") (8 . "MASONRY") (62 . 7) (370 . 13) (100 . "AcDbLine") (10 6870.8145361991
1921.1878733032 0.0) (11 6870.8145361991 1840.1208936652 0.0))
((0 . "LINE") (100 . "AcDbEntity") (8 . "MASONRY") (62 . 7) (370 . 13) (100 . "AcDbLine") (10 6874.0609954751
1414.0271493213 0.0) (11 6874.0609954751 1451.7336199095 0.0))
((0 . "LINE") (100 . "AcDbEntity") (8 . "MASONRY") (62 . 7) (370 . 13) (100 . "AcDbLine") (10 6874.0609954751
1451.7336199095 0.0) (11 7028.6573868778 1451.7336199095 0.0))
((0 . "LINE") (100 . "AcDbEntity") (8 . "MASONRY") (62 . 7) (370 . 13) (100 . "AcDbLine") (10 7028.6573868778
1451.7336199095 0.0) (11 7055.0523303167 1451.7336199095 0.0))
((0 . "LINE") (100 . "AcDbEntity") (8 . "MASONRY") (62 . 7) (370 . 13) (100 . "AcDbLine") (10 6870.2863461538
648.566199095 0.0) (11 6907.9941968326 648.566199095 0.0))
((0 . "LINE") (100 . "AcDbEntity") (8 . "MASONRY") (62 . 7) (370 . 13) (100 . "AcDbLine") (10 6881.5985633484
2748.8687782805 0.0) (11 7051.281821267 2748.8687782805 0.0))
((0 . "LINE") (100 . "AcDbEntity") (8 . "MASONRY") (62 . 7) (370 . 13) (100 . "AcDbLine") (10 6900.4524886878
1019.9844570136 0.0) (11 6881.5985633484 1019.9844570136 0.0))
((0 . "LINE") (100 . "AcDbEntity") (8 . "MASONRY") (62 . 7) (370 . 13) (100 . "AcDbLine") (10 6895.6946493213
507.8922624434 0.0) (11 6895.6946493213 520.3619909502 0.0))
((0 . "LINE") (100 . "AcDbEntity") (8 . "MASONRY") (62 . 7) (370 . 13) (100 . "AcDbLine") (10 6915.5352149321
3122.1719457014 0.0) (11 6915.5352149321 3095.7770022624 0.0))
((0 . "LINE") (100 . "AcDbEntity") (8 . "MASONRY") (62 . 7) (370 . 13) (100 . "AcDbLine") (10 6907.9941968326
2647.0588235294 0.0) (11 6907.9941968326 2635.7466063348 0.0))
((0 . "LINE") (100 . "AcDbEntity") (8 . "MASONRY") (62 . 7) (370 . 13) (100 . "AcDbLine") (10 6960.7840837104
2635.7466063348 0.0) (11 6907.9941968326 2635.7466063348 0.0))
((0 . "LINE") (100 . "AcDbEntity") (8 . "MASONRY") (62 . 7) (370 . 13) (100 . "AcDbLine") (10 7024.8868778281
2903.4693099548 0.0) (11 6911.7647058824 2903.4693099548 0.0))
((0 . "LINE") (100 . "AcDbEntity") (8 . "MASONRY") (62 . 7) (370 . 13) (100 . "AcDbLine") (10 6987.1797171946
1806.1849321267 0.0) (11 6911.7647058824 1806.1849321267 0.0))
((0 . "LINE") (100 . "AcDbEntity") (8 . "MASONRY") (62 . 7) (370 . 13) (100 . "AcDbLine") (10 6983.4085180995
784.3141855204 0.0) (11 6911.7647058824 784.3141855204 0.0))
((0 . "LINE") (100 . "AcDbEntity") (8 . "MASONRY") (62 . 7) (370 . 13) (100 . "AcDbLine") (10 6923.0769230769
2567.8733031674 0.0) (11 6923.0769230769 2556.5610859729 0.0))
((0 . "LINE") (100 . "AcDbEntity") (8 . "MASONRY") (62 . 7) (370 . 13) (100 . "AcDbLine") (10 6930.6179411765
3054.2986425339 0.0) (11 6930.6179411765 3024.1325 0.0))
((0 . "LINE") (100 . "AcDbEntity") (8 . "MASONRY") (62 . 7) (370 . 13) (100 . "AcDbLine") (10 6938.1596493213
2188.9140271493 0.0) (11 7015.460260181 2188.9140271493 0.0))
((0 . "LINE") (100 . "AcDbEntity") (8 . "MASONRY") (62 . 7) (370 . 13) (100 . "AcDbLine") (10 6950.0739366516
1165.1583710407 0.0) (11 6950.0739366516 1108.5972850679 0.0))
((0 . "LINE") (100 . "AcDbEntity") (8 . "MASONRY") (62 . 7) (370 . 13) (100 . "AcDbLine") (10 6950.0739366516
1108.5972850679 0.0) (11 6975.8668099548 1108.5972850679 0.0))
((0 . "LINE") (100 . "AcDbEntity") (8 . "MASONRY") (62 . 7) (370 . 13) (100 . "AcDbLine") (10 6950.0739366516
1165.1583710407 0.0) (11 7013.5746606335 1165.1583710407 0.0))
((0 . "LINE") (100 . "AcDbEntity") (8 . "MASONRY") (62 . 7) (370 . 13) (100 . "AcDbLine") (10 6953.2430656109
2552.7905769231 0.0) (11 6972.096300905 2552.7905769231 0.0))
((0 . "LINE") (100 . "AcDbEntity") (8 . "MASONRY") (62 . 7) (370 . 13) (100 . "AcDbLine") (10 6964.5552828054
3340.874581448 0.0) (11 6957.0135746606 3340.874581448 0.0))
((0 . "LINE") (100 . "AcDbEntity") (8 . "MASONRY") (62 . 7) (370 . 13) (100 . "AcDbLine") (10 7055.053020362
2635.7466063348 0.0) (11 7032.4285859729 2635.7466063348 0.0))
((0 . "LINE") (100 . "AcDbEntity") (8 . "MASONRY") (62 . 7) (370 . 13) (100 . "AcDbLine") (10 7032.4285859729
2635.7466063348 0.0) (11 6987.1797171946 2635.7466063348 0.0))
((0 . "LINE") (100 . "AcDbEntity") (8 . "MASONRY") (62 . 7) (370 . 13) (100 . "AcDbLine") (10 6987.1797171946
2635.7466063348 0.0) (11 6983.4085180995 2635.7466063348 0.0))
((0 . "LINE") (100 . "AcDbEntity") (8 . "MASONRY") (62 . 7) (370 . 13) (100 . "AcDbLine") (10 6983.4085180995
2635.7466063348 0.0) (11 6960.7840837104 2635.7466063348 0.0))
((0 . "LINE") (100 . "AcDbEntity") (8 . "MASONRY") (62 . 7) (370 . 13) (100 . "AcDbLine") (10 6972.096300905
3525.6412556561 0.0) (11 6972.096300905 3514.3290384615 0.0))
((0 . "LINE") (100 . "AcDbEntity") (8 . "MASONRY") (62 . 7) (370 . 13) (100 . "AcDbLine") (10 6972.096300905
3536.9534728507 0.0) (11 6972.096300905 3525.6412556561 0.0))
((0 . "LINE") (100 . "AcDbEntity") (8 . "MASONRY") (62 . 7) (370 . 13) (100 . "AcDbLine") (10 7322.7750339367
3514.3290384615 0.0) (11 6972.096300905 3514.3290384615 0.0))
((0 . "LINE") (100 . "AcDbEntity") (8 . "MASONRY") (62 . 7) (370 . 13) (100 . "AcDbLine") (10 6972.096300905
3470.9657692308 0.0) (11 6972.096300905 3514.3290384615 0.0))
((0 . "LINE") (100 . "AcDbEntity") (8 . "MASONRY") (62 . 7) (370 . 13) (100 . "AcDbLine") (10 6972.096300905
3470.9657692308 0.0) (11 7322.7750339367 3470.9657692308 0.0))
((0 . "LINE") (100 . "AcDbEntity") (8 . "MASONRY") (62 . 7) (370 . 13) (100 . "AcDbLine") (10 7032.4285859729
3095.7763122172 0.0) (11 6972.096300905 3095.7763122172 0.0))
((0 . "LINE") (100 . "AcDbEntity") (8 . "MASONRY") (62 . 7) (370 . 13) (100 . "AcDbLine") (10 6987.1797171946
3014.7058823529 0.0) (11 6972.096300905 3014.7058823529 0.0))
((0 . "LINE") (100 . "AcDbEntity") (8 . "MASONRY") (62 . 7) (370 . 13) (100 . "AcDbLine") (10 6975.8668099548
1078.4304524887 0.0) (11 6975.8668099548 1108.5972850679 0.0))
((0 . "LINE") (100 . "AcDbEntity") (8 . "MASONRY") (62 . 7) (370 . 13) (100 . "AcDbLine") (10 6979.6380090498
2581.0704298643 0.0) (11 7141.7795588235 2581.0704298643 0.0))
((0 . "LINE") (100 . "AcDbEntity") (8 . "MASONRY") (62 . 7) (370 . 13) (100 . "AcDbLine") (10 6979.6380090498
1924.9618325792 0.0) (11 7088.9896719457 1924.9618325792 0.0))
((0 . "LINE") (100 . "AcDbEntity") (8 . "MASONRY") (62 . 7) (370 . 13) (100 . "AcDbLine") (10 7349.1706674208
1108.5972850679 0.0) (11 6975.8668099548 1108.5972850679 0.0))
((0 . "LINE") (100 . "AcDbEntity") (8 . "MASONRY") (62 . 7) (370 . 13) (100 . "AcDbLine") (10 6994.7207352941
3340.874581448 0.0) (11 6983.4085180995 3340.874581448 0.0))
((0 . "LINE") (100 . "AcDbEntity") (8 . "MASONRY") (62 . 7) (370 . 13) (100 . "AcDbLine") (10 6990.9502262443
1417.7969683258 0.0) (11 7055.0523303167 1417.7969683258 0.0))
((0 . "LINE") (100 . "AcDbEntity") (8 . "MASONRY") (62 . 7) (370 . 13) (100 . "AcDbLine") (10 6994.7207352941
3129.7136538462 0.0) (11 7028.6573868778 3129.7136538462 0.0))
((0 . "LINE") (100 . "AcDbEntity") (8 . "MASONRY") (62 . 7) (370 . 13) (100 . "AcDbLine") (10 7002.2624434389
1806.1849321267 0.0) (11 7024.8868778281 1806.1849321267 0.0))
((0 . "LINE") (100 . "AcDbEntity") (8 . "MASONRY") (62 . 7) (370 . 13) (100 . "AcDbLine") (10 7043.7408031674
2107.8435972851 0.0) (11 7006.0329524887 2107.8435972851 0.0))
((0 . "LINE") (100 . "AcDbEntity") (8 . "MASONRY") (62 . 7) (370 . 13) (100 . "AcDbLine") (10 7013.5746606335
1987.1797171946 0.0) (11 7013.5746606335 2021.0390384615 0.0))
((0 . "LINE") (100 . "AcDbEntity") (8 . "MASONRY") (62 . 7) (370 . 13) (100 . "AcDbLine") (10 7013.5746606335
2021.0390384615 0.0) (11 7013.5746606335 2077.6774547511 0.0))
((0 . "LINE") (100 . "AcDbEntity") (8 . "MASONRY") (62 . 7) (370 . 13) (100 . "AcDbLine") (10 7013.5746606335
1987.1797171946 0.0) (11 7173.831300905 1987.1797171946 0.0))
((0 . "LINE") (100 . "AcDbEntity") (8 . "MASONRY") (62 . 7) (370 . 13) (100 . "AcDbLine") (10 7119.1551244344
1674.1308144796 0.0) (11 7017.3451696833 1674.1308144796 0.0))
((0 . "LINE") (100 . "AcDbEntity") (8 . "MASONRY") (62 . 7) (370 . 13) (100 . "AcDbLine") (10 7017.3451696833
1576.1680090498 0.0) (11 7017.3451696833 1621.4168778281 0.0))
((0 . "LINE") (100 . "AcDbEntity") (8 . "MASONRY") (62 . 7) (370 . 13) (100 . "AcDbLine") (10 7017.3451696833
1621.4168778281 0.0) (11 7017.3451696833 1674.1308144796 0.0))
((0 . "LINE") (100 . "AcDbEntity") (8 . "MASONRY") (62 . 7) (370 . 13) (100 . "AcDbLine") (10 7473.6050565611
2188.9140271493 0.0) (11 7134.238540724 2188.9140271493 0.0))
((0 . "LINE") (100 . "AcDbEntity") (8 . "MASONRY") (62 . 7) (370 . 13) (100 . "AcDbLine") (10 7134.238540724
2188.9140271493 0.0) (11 7015.460260181 2188.9140271493 0.0))
((0 . "LINE") (100 . "AcDbEntity") (8 . "MASONRY") (62 . 7) (370 . 13) (100 . "AcDbLine") (10 7311.4628167421
1257.467138009 0.0) (11 7292.609581448 1257.467138009 0.0))
((0 . "LINE") (100 . "AcDbEntity") (8 . "MASONRY") (62 . 7) (370 . 13) (100 . "AcDbLine") (10 7292.609581448
1257.467138009 0.0) (11 7023.0019683258 1257.467138009 0.0))
((0 . "LINE") (100 . "AcDbEntity") (8 . "MASONRY") (62 . 7) (370 . 13) (100 . "AcDbLine") (10 7023.0019683258
1206.6374208145 0.0) (11 7023.0019683258 1257.467138009 0.0))
((0 . "LINE") (100 . "AcDbEntity") (8 . "MASONRY") (62 . 7) (370 . 13) (100 . "AcDbLine") (10 7024.8868778281
2903.4693099548 0.0) (11 7024.8868778281 2911.0103280543 0.0))
((0 . "LINE") (100 . "AcDbEntity") (8 . "MASONRY") (62 . 7) (370 . 13) (100 . "AcDbLine") (10 7024.8868778281
2903.4693099548 0.0) (11 7213.424061086 2903.4693099548 0.0))
((0 . "LINE") (100 . "AcDbEntity") (8 . "MASONRY") (62 . 7) (370 . 13) (100 . "AcDbLine") (10 7224.7362782805
2371.7212217195 0.0) (11 7039.9696040724 2371.7212217195 0.0))
((0 . "LINE") (100 . "AcDbEntity") (8 . "MASONRY") (62 . 7) (370 . 13) (100 . "AcDbLine") (10 7039.9696040724
2371.7212217195 0.0) (11 7024.8868778281 2371.7212217195 0.0))
((0 . "LINE") (100 . "AcDbEntity") (8 . "MASONRY") (62 . 7) (370 . 13) (100 . "AcDbLine") (10 7024.8868778281
1806.1849321267 0.0) (11 7024.8868778281 1742.0814479638 0.0))
((0 . "LINE") (100 . "AcDbEntity") (8 . "MASONRY") (62 . 7) (370 . 13) (100 . "AcDbLine") (10 7024.8868778281
1806.1849321267 0.0) (11 7300.1505995475 1806.1849321267 0.0))
((0 . "LINE") (100 . "AcDbEntity") (8 . "MASONRY") (62 . 7) (370 . 13) (100 . "AcDbLine") (10 7126.6968325792
1742.0814479638 0.0) (11 7024.8868778281 1742.0814479638 0.0))
((0 . "LINE") (100 . "AcDbEntity") (8 . "MASONRY") (62 . 7) (370 . 13) (100 . "AcDbLine") (10 7043.7408031674
3171.1913235294 0.0) (11 7043.7408031674 3191.930158371 0.0))
((0 . "LINE") (100 . "AcDbEntity") (8 . "MASONRY") (62 . 7) (370 . 13) (100 . "AcDbLine") (10 7073.9062556561
1451.7336199095 0.0) (11 7055.0523303167 1451.7336199095 0.0))
((0 . "LINE") (100 . "AcDbEntity") (8 . "MASONRY") (62 . 7) (370 . 13) (100 . "AcDbLine") (10 7051.281821267
3337.1040723982 0.0) (11 7036.1990950226 3337.1040723982 0.0))
((0 . "LINE") (100 . "AcDbEntity") (8 . "MASONRY") (62 . 7) (370 . 13) (100 . "AcDbLine") (10 7038.0840045249
1334.8416289593 0.0) (11 7038.0840045249 1300.9049773756 0.0))
((0 . "LINE") (100 . "AcDbEntity") (8 . "MASONRY") (62 . 7) (370 . 13) (100 . "AcDbLine") (10 7038.0840045249
1334.8416289593 0.0) (11 7175.7162104072 1334.8416289593 0.0))
((0 . "LINE") (100 . "AcDbEntity") (8 . "MASONRY") (62 . 7) (370 . 13) (100 . "AcDbLine") (10 7043.7408031674
835.2191628959 0.0) (11 7036.5677941176 835.2191628959 0.0))
((0 . "LINE") (100 . "AcDbEntity") (8 . "MASONRY") (62 . 7) (370 . 13) (100 . "AcDbLine") (10 7036.5677941176
835.2191628959 0.0) (11 7036.5677941176 903.0924660633 0.0))
((0 . "LINE") (100 . "AcDbEntity") (8 . "MASONRY") (62 . 7) (370 . 13) (100 . "AcDbLine") (10 7141.7795588235
989.709219457 0.0) (11 7036.5677941176 989.709219457 0.0))
((0 . "LINE") (100 . "AcDbEntity") (8 . "MASONRY") (62 . 7) (370 . 13) (100 . "AcDbLine") (10 7036.5677941176
989.709219457 0.0) (11 7036.5677941176 903.0924660633 0.0))
((0 . "LINE") (100 . "AcDbEntity") (8 . "MASONRY") (62 . 7) (370 . 13) (100 . "AcDbLine") (10 7122.9263235294
903.0924660633 0.0) (11 7036.5677941176 903.0924660633 0.0))
((0 . "LINE") (100 . "AcDbEntity") (8 . "MASONRY") (62 . 7) (370 . 13) (100 . "AcDbLine") (10 7043.7408031674
3212.6696832579 0.0) (11 7043.7408031674 3191.930158371 0.0))
((0 . "LINE") (100 . "AcDbEntity") (8 . "MASONRY") (62 . 7) (370 . 13) (100 . "AcDbLine") (10 7077.6774547511
3191.930158371 0.0) (11 7043.7408031674 3191.930158371 0.0))
((0 . "LINE") (100 . "AcDbEntity") (8 . "MASONRY") (62 . 7) (370 . 13) (100 . "AcDbLine") (10 7055.0523303167
1451.7336199095 0.0) (11 7055.0523303167 1417.7969683258 0.0))
((0 . "LINE") (100 . "AcDbEntity") (8 . "MASONRY") (62 . 7) (370 . 13) (100 . "AcDbLine") (10 7051.281821267
3048.6425339367 0.0) (11 7213.424061086 3048.6425339367 0.0))
((0 . "LINE") (100 . "AcDbEntity") (8 . "MASONRY") (62 . 7) (370 . 13) (100 . "AcDbLine") (10 7051.281821267
2748.8687782805 0.0) (11 7051.281821267 2722.4738348416 0.0))
((0 . "LINE") (100 . "AcDbEntity") (8 . "MASONRY") (62 . 7) (370 . 13) (100 . "AcDbLine") (10 7164.4039932127
2748.8687782805 0.0) (11 7051.281821267 2748.8687782805 0.0))
((0 . "LINE") (100 . "AcDbEntity") (8 . "MASONRY") (62 . 7) (370 . 13) (100 . "AcDbLine") (10 7055.053020362
2635.7466063348 0.0) (11 7153.0917760181 2635.7466063348 0.0))
((0 . "LINE") (100 . "AcDbEntity") (8 . "MASONRY") (62 . 7) (370 . 13) (100 . "AcDbLine") (10 7055.053020362
1625.1894570136 0.0) (11 7426.4705882353 1625.1894570136 0.0))
((0 . "LINE") (100 . "AcDbEntity") (8 . "MASONRY") (62 . 7) (370 . 13) (100 . "AcDbLine") (10 7058.8235294118
2111.6141063348 0.0) (11 7633.8616968326 2111.6141063348 0.0))
((0 . "LINE") (100 . "AcDbEntity") (8 . "MASONRY") (62 . 7) (370 . 13) (100 . "AcDbLine") (10 7467.9482579186
1417.7969683258 0.0) (11 7190.7996266968 1417.7969683258 0.0))
((0 . "LINE") (100 . "AcDbEntity") (8 . "MASONRY") (62 . 7) (370 . 13) (100 . "AcDbLine") (10 7190.7996266968
1417.7969683258 0.0) (11 7164.4039932127 1417.7969683258 0.0))
((0 . "LINE") (100 . "AcDbEntity") (8 . "MASONRY") (62 . 7) (370 . 13) (100 . "AcDbLine") (10 7164.4039932127
1417.7969683258 0.0) (11 7055.0523303167 1417.7969683258 0.0))
((0 . "LINE") (100 . "AcDbEntity") (8 . "MASONRY") (62 . 7) (370 . 13) (100 . "AcDbLine") (10 7062.5940384615
1168.9281900452 0.0) (11 7115.3846153846 1168.9281900452 0.0))
((0 . "LINE") (100 . "AcDbEntity") (8 . "MASONRY") (62 . 7) (370 . 13) (100 . "AcDbLine") (10 7073.9062556561
1451.7336199095 0.0) (11 7130.467341629 1451.7336199095 0.0))
((0 . "LINE") (100 . "AcDbEntity") (8 . "MASONRY") (62 . 7) (370 . 13) (100 . "AcDbLine") (10 7277.5261651584
1549.7737556561 0.0) (11 7077.6774547511 1549.7737556561 0.0))
((0 . "LINE") (100 . "AcDbEntity") (8 . "MASONRY") (62 . 7) (370 . 13) (100 . "AcDbLine") (10 7030.8978733032
682.5774208145 0.0) (11 6987.134841629 682.5774208145 0.0))
((0 . "LINE") (100 . "AcDbEntity") (8 . "MASONRY") (62 . 7) (370 . 13) (100 . "AcDbLine") (10 6987.134841629
682.5774208145 0.0) (11 6987.134841629 599.5675339367 0.0))
((0 . "LINE") (100 . "AcDbEntity") (8 . "MASONRY") (62 . 7) (370 . 13) (100 . "AcDbLine") (10 7175.7162104072
3342.7601809955 0.0) (11 7081.4479638009 3342.7601809955 0.0))
((0 . "LINE") (100 . "AcDbEntity") (8 . "MASONRY") (62 . 7) (370 . 13) (100 . "AcDbLine") (10 7209.652861991
3190.0452488688 0.0) (11 7115.3846153846 3190.0452488688 0.0))
((0 . "LINE") (100 . "AcDbEntity") (8 . "MASONRY") (62 . 7) (370 . 13) (100 . "AcDbLine") (10 7126.6968325792
1742.0814479638 0.0) (11 7126.6968325792 1708.1447963801 0.0))
((0 . "LINE") (100 . "AcDbEntity") (8 . "MASONRY") (62 . 7) (370 . 13) (100 . "AcDbLine") (10 7126.6968325792
1742.0814479638 0.0) (11 7334.0872511312 1742.0814479638 0.0))
((0 . "LINE") (100 . "AcDbEntity") (8 . "MASONRY") (62 . 7) (370 . 13) (100 . "AcDbLine") (10 7168.1751923077
1167.043280543 0.0) (11 7126.6968325792 1167.043280543 0.0))
((0 . "LINE") (100 . "AcDbEntity") (8 . "MASONRY") (62 . 7) (370 . 13) (100 . "AcDbLine") (10 7139.893959276
2254.9017307692 0.0) (11 7139.893959276 2271.8707466063 0.0))
((0 . "LINE") (100 . "AcDbEntity") (8 . "MASONRY") (62 . 7) (370 . 13) (100 . "AcDbLine") (10 7139.893959276
2271.8707466063 0.0) (11 7224.7362782805 2271.8707466063 0.0))
((0 . "LINE") (100 . "AcDbEntity") (8 . "MASONRY") (62 . 7) (370 . 13) (100 . "AcDbLine") (10 7205.8823529412
2547.1344683258 0.0) (11 7145.5507579186 2547.1344683258 0.0))
((0 . "LINE") (100 . "AcDbEntity") (8 . "MASONRY") (62 . 7) (370 . 13) (100 . "AcDbLine") (10 7153.0917760181
2635.7466063348 0.0) (11 7153.0917760181 2620.6638800905 0.0))
((0 . "LINE") (100 . "AcDbEntity") (8 . "MASONRY") (62 . 7) (370 . 13) (100 . "AcDbLine") (10 7153.0917760181
2635.7466063348 0.0) (11 7213.424061086 2635.7466063348 0.0))
((0 . "LINE") (100 . "AcDbEntity") (8 . "MASONRY") (62 . 7) (370 . 13) (100 . "AcDbLine") (10 7175.7162104072
1926.8474321267 0.0) (11 7156.8629751131 1926.8474321267 0.0))
((0 . "LINE") (100 . "AcDbEntity") (8 . "MASONRY") (62 . 7) (370 . 13) (100 . "AcDbLine") (10 7164.4039932127
2771.4932126697 0.0) (11 7164.4039932127 2748.8687782805 0.0))
((0 . "LINE") (100 . "AcDbEntity") (8 . "MASONRY") (62 . 7) (370 . 13) (100 . "AcDbLine") (10 7177.6018099548
2748.8687782805 0.0) (11 7164.4039932127 2748.8687782805 0.0))
((0 . "LINE") (100 . "AcDbEntity") (8 . "MASONRY") (62 . 7) (370 . 13) (100 . "AcDbLine") (10 7190.7996266968
1014.4767986425 0.0) (11 7164.4039932127 1014.4767986425 0.0))
((0 . "LINE") (100 . "AcDbEntity") (8 . "MASONRY") (62 . 7) (370 . 13) (100 . "AcDbLine") (10 7179.4874095023
1987.1797171946 0.0) (11 7173.831300905 1987.1797171946 0.0))
((0 . "LINE") (100 . "AcDbEntity") (8 . "MASONRY") (62 . 7) (370 . 13) (100 . "AcDbLine") (10 7173.831300905
1987.1797171946 0.0) (11 7173.831300905 2009.8041515837 0.0))
((0 . "LINE") (100 . "AcDbEntity") (8 . "MASONRY") (62 . 7) (370 . 13) (100 . "AcDbLine") (10 7175.7162104072
1926.8474321267 0.0) (11 7175.7162104072 1864.6309276018 0.0))
((0 . "LINE") (100 . "AcDbEntity") (8 . "MASONRY") (62 . 7) (370 . 13) (100 . "AcDbLine") (10 7175.7162104072
1864.6309276018 0.0) (11 7328.4318325792 1864.6309276018 0.0))
((0 . "LINE") (100 . "AcDbEntity") (8 . "MASONRY") (62 . 7) (370 . 13) (100 . "AcDbLine") (10 7175.7162104072
1934.3891402715 0.0) (11 7175.7162104072 1926.8474321267 0.0))
((0 . "LINE") (100 . "AcDbEntity") (8 . "MASONRY") (62 . 7) (370 . 13) (100 . "AcDbLine") (10 7177.6018099548
3367.2702149321 0.0) (11 7177.6018099548 3404.9773755656 0.0))
((0 . "LINE") (100 . "AcDbEntity") (8 . "MASONRY") (62 . 7) (370 . 13) (100 . "AcDbLine") (10 7175.7162104072
3288.0846945701 0.0) (11 7175.7162104072 3257.9185520362 0.0))
((0 . "LINE") (100 . "AcDbEntity") (8 . "MASONRY") (62 . 7) (370 . 13) (100 . "AcDbLine") (10 7175.7162104072
3257.9185520362 0.0) (11 7213.424061086 3257.9185520362 0.0))
((0 . "LINE") (100 . "AcDbEntity") (8 . "MASONRY") (62 . 7) (370 . 13) (100 . "AcDbLine") (10 7177.6018099548
2748.8687782805 0.0) (11 7213.424061086 2748.8687782805 0.0))
((0 . "LINE") (100 . "AcDbEntity") (8 . "MASONRY") (62 . 7) (370 . 13) (100 . "AcDbLine") (10 7177.6018099548
2748.8687782805 0.0) (11 7177.6018099548 2722.4738348416 0.0))
((0 . "LINE") (100 . "AcDbEntity") (8 . "MASONRY") (62 . 7) (370 . 13) (100 . "AcDbLine") (10 7175.7162104072
1334.8416289593 0.0) (11 7175.7162104072 1376.320678733 0.0))
((0 . "LINE") (100 . "AcDbEntity") (8 . "MASONRY") (62 . 7) (370 . 13) (100 . "AcDbLine") (10 7688.5378733032
1334.8416289593 0.0) (11 7175.7162104072 1334.8416289593 0.0))
((0 . "LINE") (100 . "AcDbEntity") (8 . "MASONRY") (62 . 7) (370 . 13) (100 . "AcDbLine") (10 7179.4874095023
874.8105429864 0.0) (11 7179.4874095023 867.2709049774 0.0))
((0 . "LINE") (100 . "AcDbEntity") (8 . "MASONRY") (62 . 7) (370 . 13) (100 . "AcDbLine") (10 7179.4874095023
867.2709049774 0.0) (11 7179.4874095023 814.479638009 0.0))
((0 . "LINE") (100 . "AcDbEntity") (8 . "MASONRY") (62 . 7) (370 . 13) (100 . "AcDbLine") (10 7179.4874095023
814.479638009 0.0) (11 7179.4874095023 778.1526696833 0.0))
((0 . "LINE") (100 . "AcDbEntity") (8 . "MASONRY") (62 . 7) (370 . 13) (100 . "AcDbLine") (10 7179.4874095023
778.1526696833 0.0) (11 7179.4874095023 774.1102941176 0.0))
((0 . "LINE") (100 . "AcDbEntity") (8 . "MASONRY") (62 . 7) (370 . 13) (100 . "AcDbLine") (10 7190.7996266968
1468.7033257919 0.0) (11 7183.257918552 1468.7033257919 0.0))
((0 . "LINE") (100 . "AcDbEntity") (8 . "MASONRY") (62 . 7) (370 . 13) (100 . "AcDbLine") (10 7183.257918552
1165.1583710407 0.0) (11 7220.9650791855 1165.1583710407 0.0))
((0 . "LINE") (100 . "AcDbEntity") (8 . "MASONRY") (62 . 7) (370 . 13) (100 . "AcDbLine") (10 7194.5701357466
764.1919117647 0.0) (11 7189.4967647059 764.1919117647 0.0))
((0 . "LINE") (100 . "AcDbEntity") (8 . "MASONRY") (62 . 7) (370 . 13) (100 . "AcDbLine") (10 7190.7996266968
1014.4767986425 0.0) (11 7190.7996266968 938.9140271493 0.0))
((0 . "LINE") (100 . "AcDbEntity") (8 . "MASONRY") (62 . 7) (370 . 13) (100 . "AcDbLine") (10 7190.7996266968
1014.4767986425 0.0) (11 7373.6807013575 1014.4767986425 0.0))
((0 . "LINE") (100 . "AcDbEntity") (8 . "MASONRY") (62 . 7) (370 . 13) (100 . "AcDbLine") (10 7228.5067873303
2013.5746606335 0.0) (11 7213.424061086 2013.5746606335 0.0))
((0 . "LINE") (100 . "AcDbEntity") (8 . "MASONRY") (62 . 7) (370 . 13) (100 . "AcDbLine") (10 7492.4582918552
2271.8707466063 0.0) (11 7243.5895135747 2271.8707466063 0.0))
((0 . "LINE") (100 . "AcDbEntity") (8 . "MASONRY") (62 . 7) (370 . 13) (100 . "AcDbLine") (10 7243.5895135747
2271.8707466063 0.0) (11 7224.7362782805 2271.8707466063 0.0))
((0 . "LINE") (100 . "AcDbEntity") (8 . "MASONRY") (62 . 7) (370 . 13) (100 . "AcDbLine") (10 7224.7362782805
2328.4318325792 0.0) (11 7224.7362782805 2271.8707466063 0.0))
((0 . "LINE") (100 . "AcDbEntity") (8 . "MASONRY") (62 . 7) (370 . 13) (100 . "AcDbLine") (10 7224.7362782805
2328.4318325792 0.0) (11 7224.7362782805 2371.7212217195 0.0))
((0 . "LINE") (100 . "AcDbEntity") (8 . "MASONRY") (62 . 7) (370 . 13) (100 . "AcDbLine") (10 7224.7362782805
2371.7212217195 0.0) (11 7288.8383823529 2371.7212217195 0.0))
((0 . "LINE") (100 . "AcDbEntity") (8 . "MASONRY") (62 . 7) (370 . 13) (100 . "AcDbLine") (10 7224.7362782805
2328.4318325792 0.0) (11 7466.0633484163 2328.4318325792 0.0))
((0 . "LINE") (100 . "AcDbEntity") (8 . "MASONRY") (62 . 7) (370 . 13) (100 . "AcDbLine") (10 7262.443438914
1466.8170361991 0.0) (11 7228.5067873303 1466.8170361991 0.0))
((0 . "LINE") (100 . "AcDbEntity") (8 . "MASONRY") (62 . 7) (370 . 13) (100 . "AcDbLine") (10 7273.7556561086
912.5197737557 0.0) (11 7232.2772963801 912.5197737557 0.0))
((0 . "LINE") (100 . "AcDbEntity") (8 . "MASONRY") (62 . 7) (370 . 13) (100 . "AcDbLine") (10 7262.443438914
1165.1583710407 0.0) (11 7251.1312217195 1165.1583710407 0.0))
((0 . "LINE") (100 . "AcDbEntity") (8 . "MASONRY") (62 . 7) (370 . 13) (100 . "AcDbLine") (10 7273.7556561086
886.122760181 0.0) (11 7254.9017307692 886.122760181 0.0))
((0 . "LINE") (100 . "AcDbEntity") (8 . "MASONRY") (62 . 7) (370 . 13) (100 . "AcDbLine") (10 7262.443438914
1187.7828054299 0.0) (11 7262.443438914 1165.1583710407 0.0))
((0 . "LINE") (100 . "AcDbEntity") (8 . "MASONRY") (62 . 7) (370 . 13) (100 . "AcDbLine") (10 7277.5261651584
2011.6897511312 0.0) (11 7269.9851470588 2011.6897511312 0.0))
((0 . "LINE") (100 . "AcDbEntity") (8 . "MASONRY") (62 . 7) (370 . 13) (100 . "AcDbLine") (10 7345.3994683258
912.5197737557 0.0) (11 7273.7556561086 912.5197737557 0.0))
((0 . "LINE") (100 . "AcDbEntity") (8 . "MASONRY") (62 . 7) (370 . 13) (100 . "AcDbLine") (10 7273.7556561086
912.5197737557 0.0) (11 7273.7556561086 886.122760181 0.0))
((0 . "LINE") (100 . "AcDbEntity") (8 . "MASONRY") (62 . 7) (370 . 13) (100 . "AcDbLine") (10 7338.7739819005
886.122760181 0.0) (11 7273.7556561086 886.122760181 0.0))
((0 . "LINE") (100 . "AcDbEntity") (8 . "MASONRY") (62 . 7) (370 . 13) (100 . "AcDbLine") (10 7288.8383823529
824.7161425339 0.0) (11 7324.9561425339 824.7161425339 0.0))
((0 . "LINE") (100 . "AcDbEntity") (8 . "MASONRY") (62 . 7) (370 . 13) (100 . "AcDbLine") (10 7292.609581448
1197.2087330317 0.0) (11 7311.4628167421 1197.2087330317 0.0))
((0 . "LINE") (100 . "AcDbEntity") (8 . "MASONRY") (62 . 7) (370 . 13) (100 . "AcDbLine") (10 7309.5772171946
1546.0025565611 0.0) (11 7296.3800904977 1546.0025565611 0.0))
((0 . "LINE") (100 . "AcDbEntity") (8 . "MASONRY") (62 . 7) (370 . 13) (100 . "AcDbLine") (10 7300.1505995475
1461.1609276018 0.0) (11 7307.6923076923 1461.1609276018 0.0))
((0 . "LINE") (100 . "AcDbEntity") (8 . "MASONRY") (62 . 7) (370 . 13) (100 . "AcDbLine") (10 7307.6923076923
2388.7634276018 0.0) (11 7322.7750339367 2388.7634276018 0.0))
((0 . "LINE") (100 . "AcDbEntity") (8 . "MASONRY") (62 . 7) (370 . 13) (100 . "AcDbLine") (10 7322.7750339367
2388.7634276018 0.0) (11 7322.7750339367 2428.3561877828 0.0))
((0 . "LINE") (100 . "AcDbEntity") (8 . "MASONRY") (62 . 7) (370 . 13) (100 . "AcDbLine") (10 7567.8733031674
1546.0025565611 0.0) (11 7319.0045248869 1546.0025565611 0.0))
((0 . "LINE") (100 . "AcDbEntity") (8 . "MASONRY") (62 . 7) (370 . 13) (100 . "AcDbLine") (10 7319.0045248869
1546.0025565611 0.0) (11 7309.5772171946 1546.0025565611 0.0))
((0 . "LINE") (100 . "AcDbEntity") (8 . "MASONRY") (62 . 7) (370 . 13) (100 . "AcDbLine") (10 7309.5772171946
1583.7104072398 0.0) (11 7309.5772171946 1546.0025565611 0.0))
((0 . "LINE") (100 . "AcDbEntity") (8 . "MASONRY") (62 . 7) (370 . 13) (100 . "AcDbLine") (10 7311.4628167421
1312.2171945701 0.0) (11 7311.4628167421 1297.135158371 0.0))
((0 . "LINE") (100 . "AcDbEntity") (8 . "MASONRY") (62 . 7) (370 . 13) (100 . "AcDbLine") (10 7375.5656108597
1161.3885520362 0.0) (11 7311.4628167421 1161.3885520362 0.0))
((0 . "LINE") (100 . "AcDbEntity") (8 . "MASONRY") (62 . 7) (370 . 13) (100 . "AcDbLine") (10 7315.2340158371
2496.2294909502 0.0) (11 7330.3167420814 2496.2294909502 0.0))
((0 . "LINE") (100 . "AcDbEntity") (8 . "MASONRY") (62 . 7) (370 . 13) (100 . "AcDbLine") (10 7328.4318325792
1809.9547511312 0.0) (11 7315.2340158371 1809.9547511312 0.0))
((0 . "LINE") (100 . "AcDbEntity") (8 . "MASONRY") (62 . 7) (370 . 13) (100 . "AcDbLine") (10 7322.7750339367
3470.9657692308 0.0) (11 7322.7750339367 3514.3290384615 0.0))
((0 . "LINE") (100 . "AcDbEntity") (8 . "MASONRY") (62 . 7) (370 . 13) (100 . "AcDbLine") (10 7322.7750339367
3536.9534728507 0.0) (11 7322.7750339367 3514.3290384615 0.0))
((0 . "LINE") (100 . "AcDbEntity") (8 . "MASONRY") (62 . 7) (370 . 13) (100 . "AcDbLine") (10 7319.0045248869
1973.9819004525 0.0) (11 7368.0239027149 1973.9819004525 0.0))
((0 . "LINE") (100 . "AcDbEntity") (8 . "MASONRY") (62 . 7) (370 . 13) (100 . "AcDbLine") (10 7322.7750339367
2428.3561877828 0.0) (11 7322.7750339367 2458.5216402715 0.0))
((0 . "LINE") (100 . "AcDbEntity") (8 . "MASONRY") (62 . 7) (370 . 13) (100 . "AcDbLine") (10 7322.7750339367
2428.3561877828 0.0) (11 7456.636040724 2428.3561877828 0.0))
((0 . "LINE") (100 . "AcDbEntity") (8 . "MASONRY") (62 . 7) (370 . 13) (100 . "AcDbLine") (10 7322.7750339367
3470.9657692308 0.0) (11 7865.7607692308 3470.9657692308 0.0))
((0 . "LINE") (100 . "AcDbEntity") (8 . "MASONRY") (62 . 7) (370 . 13) (100 . "AcDbLine") (10 7371.79510181
2011.6897511312 0.0) (11 7326.5462330317 2011.6897511312 0.0))
((0 . "LINE") (100 . "AcDbEntity") (8 . "MASONRY") (62 . 7) (370 . 13) (100 . "AcDbLine") (10 7328.4318325792
1864.6309276018 0.0) (11 7328.4318325792 1809.9547511312 0.0))
((0 . "LINE") (100 . "AcDbEntity") (8 . "MASONRY") (62 . 7) (370 . 13) (100 . "AcDbLine") (10 7415.1583710407
1864.6309276018 0.0) (11 7328.4318325792 1864.6309276018 0.0))
((0 . "LINE") (100 . "AcDbEntity") (8 . "MASONRY") (62 . 7) (370 . 13) (100 . "AcDbLine") (10 7492.4582918552
1809.9547511312 0.0) (11 7328.4318325792 1809.9547511312 0.0))
((0 . "LINE") (100 . "AcDbEntity") (8 . "MASONRY") (62 . 7) (370 . 13) (100 . "AcDbLine") (10 7334.0872511312
1768.4757013575 0.0) (11 7334.0872511312 1742.0814479638 0.0))
((0 . "LINE") (100 . "AcDbEntity") (8 . "MASONRY") (62 . 7) (370 . 13) (100 . "AcDbLine") (10 7492.4582918552
1742.0814479638 0.0) (11 7334.0872511312 1742.0814479638 0.0))
((0 . "LINE") (100 . "AcDbEntity") (8 . "MASONRY") (62 . 7) (370 . 13) (100 . "AcDbLine") (10 7345.3994683258
912.5197737557 0.0) (11 7345.3994683258 885.4958371041 0.0))
((0 . "LINE") (100 . "AcDbEntity") (8 . "MASONRY") (62 . 7) (370 . 13) (100 . "AcDbLine") (10 7345.3994683258
912.5197737557 0.0) (11 7364.2533936652 912.5197737557 0.0))
((0 . "LINE") (100 . "AcDbEntity") (8 . "MASONRY") (62 . 7) (370 . 13) (100 . "AcDbLine") (10 7347.1138348416
881.7819457014 0.0) (11 7356.1676131222 881.7819457014 0.0))
((0 . "LINE") (100 . "AcDbEntity") (8 . "MASONRY") (62 . 7) (370 . 13) (100 . "AcDbLine") (10 7374.6224660633
823.9856561086 0.0) (11 7401.9605542986 823.9856561086 0.0))
((0 . "LINE") (100 . "AcDbEntity") (8 . "MASONRY") (62 . 7) (370 . 13) (100 . "AcDbLine") (10 7356.1676131222
863.3450452489 0.0) (11 7356.1676131222 881.7819457014 0.0))
((0 . "LINE") (100 . "AcDbEntity") (8 . "MASONRY") (62 . 7) (370 . 13) (100 . "AcDbLine") (10 7462.2928393665
881.7819457014 0.0) (11 7356.1676131222 881.7819457014 0.0))
((0 . "LINE") (100 . "AcDbEntity") (8 . "MASONRY") (62 . 7) (370 . 13) (100 . "AcDbLine") (10 7594.2675565611
1259.4273076923 0.0) (11 7360.4828846154 1259.4273076923 0.0))
((0 . "LINE") (100 . "AcDbEntity") (8 . "MASONRY") (62 . 7) (370 . 13) (100 . "AcDbLine") (10 7500 1104.8274660633 0.0)
(11 7500 1087.9350904977 0.0))
((0 . "LINE") (100 . "AcDbEntity") (8 . "MASONRY") (62 . 7) (370 . 13) (100 . "AcDbLine") (10 7500 1087.9350904977 0.0)
(11 7371.79510181 1087.9350904977 0.0))
((0 . "LINE") (100 . "AcDbEntity") (8 . "MASONRY") (62 . 7) (370 . 13) (100 . "AcDbLine") (10 7373.6807013575
1055.8060180995 0.0) (11 7373.6807013575 1014.4767986425 0.0))
((0 . "LINE") (100 . "AcDbEntity") (8 . "MASONRY") (62 . 7) (370 . 13) (100 . "AcDbLine") (10 7435.8260859729
747.234638009 0.0) (11 7435.8260859729 812.5167081448 0.0))
((0 . "LINE") (100 . "AcDbEntity") (8 . "MASONRY") (62 . 7) (370 . 13) (100 . "AcDbLine") (10 7435.8260859729
812.5167081448 0.0) (11 7490.0451923077 812.5167081448 0.0))
((0 . "LINE") (100 . "AcDbEntity") (8 . "MASONRY") (62 . 7) (370 . 13) (100 . "AcDbLine") (10 7375.5656108597
1127.4519004525 0.0) (11 7375.5656108597 1161.3885520362 0.0))
((0 . "LINE") (100 . "AcDbEntity") (8 . "MASONRY") (62 . 7) (370 . 13) (100 . "AcDbLine") (10 7462.2928393665
1161.3885520362 0.0) (11 7375.5656108597 1161.3885520362 0.0))
((0 . "LINE") (100 . "AcDbEntity") (8 . "MASONRY") (62 . 7) (370 . 13) (100 . "AcDbLine") (10 7481.1460746606
1014.4767986425 0.0) (11 7409.5022624434 1014.4767986425 0.0))
((0 . "LINE") (100 . "AcDbEntity") (8 . "MASONRY") (62 . 7) (370 . 13) (100 . "AcDbLine") (10 7409.5022624434
1014.4767986425 0.0) (11 7373.6807013575 1014.4767986425 0.0))
((0 . "LINE") (100 . "AcDbEntity") (8 . "MASONRY") (62 . 7) (370 . 13) (100 . "AcDbLine") (10 7490.0451923077
664.2496153846 0.0) (11 7490.0451923077 791.8552036199 0.0))
((0 . "LINE") (100 . "AcDbEntity") (8 . "MASONRY") (62 . 7) (370 . 13) (100 . "AcDbLine") (10 7490.0451923077
791.8552036199 0.0) (11 7490.0451923077 812.5167081448 0.0))
((0 . "LINE") (100 . "AcDbEntity") (8 . "MASONRY") (62 . 7) (370 . 13) (100 . "AcDbLine") (10 7417.043280543
1896.681979638 0.0) (11 7417.043280543 1915.5352149321 0.0))
((0 . "LINE") (100 . "AcDbEntity") (8 . "MASONRY") (62 . 7) (370 . 13) (100 . "AcDbLine") (10 7415.1583710407
1864.6309276018 0.0) (11 7415.1583710407 1877.8280542986 0.0))
((0 . "LINE") (100 . "AcDbEntity") (8 . "MASONRY") (62 . 7) (370 . 13) (100 . "AcDbLine") (10 7415.1583710407
1864.6309276018 0.0) (11 7435.8972058824 1864.6309276018 0.0))
((0 . "LINE") (100 . "AcDbEntity") (8 . "MASONRY") (62 . 7) (370 . 13) (100 . "AcDbLine") (10 7419.0062104072
2013.5746606335 0.0) (11 7419.0062104072 1953.3908257919 0.0))
((0 . "LINE") (100 . "AcDbEntity") (8 . "MASONRY") (62 . 7) (370 . 13) (100 . "AcDbLine") (10 7419.0062104072
1953.3908257919 0.0) (11 7439.6684049774 1953.3908257919 0.0))
((0 . "LINE") (100 . "AcDbEntity") (8 . "MASONRY") (62 . 7) (370 . 13) (100 . "AcDbLine") (10 7439.6684049774
1953.3908257919 0.0) (11 7726.2443438914 1953.3908257919 0.0))
((0 . "LINE") (100 . "AcDbEntity") (8 . "MASONRY") (62 . 7) (370 . 13) (100 . "AcDbLine") (10 7435.8972058824
1625.1894570136 0.0) (11 7426.4705882353 1625.1894570136 0.0))
((0 . "LINE") (100 . "AcDbEntity") (8 . "MASONRY") (62 . 7) (370 . 13) (100 . "AcDbLine") (10 7426.4705882353
1644.0413122172 0.0) (11 7426.4705882353 1625.1894570136 0.0))
((0 . "LINE") (100 . "AcDbEntity") (8 . "MASONRY") (62 . 7) (370 . 13) (100 . "AcDbLine") (10 7437.7828054299
1372.5480995475 0.0) (11 7437.7828054299 1365.0084615385 0.0))
((0 . "LINE") (100 . "AcDbEntity") (8 . "MASONRY") (62 . 7) (370 . 13) (100 . "AcDbLine") (10 7492.4582918552
2775.2637217195 0.0) (11 7454.7511312217 2775.2637217195 0.0))
((0 . "LINE") (100 . "AcDbEntity") (8 . "MASONRY") (62 . 7) (370 . 13) (100 . "AcDbLine") (10 7696.0775113122
2503.7705090498 0.0) (11 7454.7511312217 2503.7705090498 0.0))
((0 . "LINE") (100 . "AcDbEntity") (8 . "MASONRY") (62 . 7) (370 . 13) (100 . "AcDbLine") (10 7456.636040724
2375.5656108597 0.0) (11 7456.636040724 2428.3561877828 0.0))
((0 . "LINE") (100 . "AcDbEntity") (8 . "MASONRY") (62 . 7) (370 . 13) (100 . "AcDbLine") (10 7456.636040724
2428.3561877828 0.0) (11 7599.9236651584 2428.3561877828 0.0))
((0 . "LINE") (100 . "AcDbEntity") (8 . "MASONRY") (62 . 7) (370 . 13) (100 . "AcDbLine") (10 7458.5216402715
3412.5190837104 0.0) (11 7458.5216402715 3404.9773755656 0.0))
((0 . "LINE") (100 . "AcDbEntity") (8 . "MASONRY") (62 . 7) (370 . 13) (100 . "AcDbLine") (10 7865.7607692308
3340.874581448 0.0) (11 7458.5216402715 3340.874581448 0.0))
((0 . "LINE") (100 . "AcDbEntity") (8 . "MASONRY") (62 . 7) (370 . 13) (100 . "AcDbLine") (10 7869.5333484163
3267.3451696833 0.0) (11 7458.5216402715 3267.3451696833 0.0))
((0 . "LINE") (100 . "AcDbEntity") (8 . "MASONRY") (62 . 7) (370 . 13) (100 . "AcDbLine") (10 7458.5216402715
3191.930158371 0.0) (11 7869.5333484163 3191.930158371 0.0))
((0 . "LINE") (100 . "AcDbEntity") (8 . "MASONRY") (62 . 7) (370 . 13) (100 . "AcDbLine") (10 7500 2818.6269909502 0.0)
(11 7458.5216402715 2818.6269909502 0.0))
((0 . "LINE") (100 . "AcDbEntity") (8 . "MASONRY") (62 . 7) (370 . 13) (100 . "AcDbLine") (10 7458.5216402715
2633.8616968326 0.0) (11 7618.778280543 2633.8616968326 0.0))
((0 . "LINE") (100 . "AcDbEntity") (8 . "MASONRY") (62 . 7) (370 . 13) (100 . "AcDbLine") (10 7460.407239819
2564.1027941176 0.0) (11 7460.407239819 2575.4150113122 0.0))
((0 . "LINE") (100 . "AcDbEntity") (8 . "MASONRY") (62 . 7) (370 . 13) (100 . "AcDbLine") (10 7458.5216402715
1860.78239819 0.0) (11 7492.4582918552 1860.78239819 0.0))
((0 . "LINE") (100 . "AcDbEntity") (8 . "MASONRY") (62 . 7) (370 . 13) (100 . "AcDbLine") (10 7492.4582918552
1860.78239819 0.0) (11 7492.4582918552 1809.9547511312 0.0))
((0 . "LINE") (100 . "AcDbEntity") (8 . "MASONRY") (62 . 7) (370 . 13) (100 . "AcDbLine") (10 7869.5333484163
2894.0426923077 0.0) (11 7462.2928393665 2894.0426923077 0.0))
((0 . "LINE") (100 . "AcDbEntity") (8 . "MASONRY") (62 . 7) (370 . 13) (100 . "AcDbLine") (10 7466.0633484163
3120.2870361991 0.0) (11 7533.9366515837 3120.2870361991 0.0))
((0 . "LINE") (100 . "AcDbEntity") (8 . "MASONRY") (62 . 7) (370 . 13) (100 . "AcDbLine") (10 7466.0633484163
3046.7569343891 0.0) (11 7650.8286425339 3046.7569343891 0.0))
((0 . "LINE") (100 . "AcDbEntity") (8 . "MASONRY") (62 . 7) (370 . 13) (100 . "AcDbLine") (10 7466.0633484163
2969.4570135747 0.0) (11 7598.0401357466 2969.4570135747 0.0))
((0 . "LINE") (100 . "AcDbEntity") (8 . "MASONRY") (62 . 7) (370 . 13) (100 . "AcDbLine") (10 7467.9482579186
1417.7969683258 0.0) (11 7467.9482579186 1402.7149321267 0.0))
((0 . "LINE") (100 . "AcDbEntity") (8 . "MASONRY") (62 . 7) (370 . 13) (100 . "AcDbLine") (10 7861.9909502262
1417.7969683258 0.0) (11 7726.2443438914 1417.7969683258 0.0))
((0 . "LINE") (100 . "AcDbEntity") (8 . "MASONRY") (62 . 7) (370 . 13) (100 . "AcDbLine") (10 7726.2443438914
1417.7969683258 0.0) (11 7613.1221719457 1417.7969683258 0.0))
((0 . "LINE") (100 . "AcDbEntity") (8 . "MASONRY") (62 . 7) (370 . 13) (100 . "AcDbLine") (10 7613.1221719457
1417.7969683258 0.0) (11 7467.9482579186 1417.7969683258 0.0))
((0 . "LINE") (100 . "AcDbEntity") (8 . "MASONRY") (62 . 7) (370 . 13) (100 . "AcDbLine") (10 7473.6050565611
2188.9140271493 0.0) (11 7473.6050565611 2217.1945701357 0.0))
((0 . "LINE") (100 . "AcDbEntity") (8 . "MASONRY") (62 . 7) (370 . 13) (100 . "AcDbLine") (10 7473.6050565611
2188.9140271493 0.0) (11 7479.2604751131 2188.9140271493 0.0))
((0 . "LINE") (100 . "AcDbEntity") (8 . "MASONRY") (62 . 7) (370 . 13) (100 . "AcDbLine") (10 7479.2604751131
2153.0917760181 0.0) (11 7479.2604751131 2188.9140271493 0.0))
((0 . "LINE") (100 . "AcDbEntity") (8 . "MASONRY") (62 . 7) (370 . 13) (100 . "AcDbLine") (10 7477.3755656109
1617.6470588235 0.0) (11 7522.6244343891 1617.6470588235 0.0))
((0 . "LINE") (100 . "AcDbEntity") (8 . "MASONRY") (62 . 7) (370 . 13) (100 . "AcDbLine") (10 7477.3755656109
1161.3885520362 0.0) (11 7492.4582918552 1161.3885520362 0.0))
((0 . "LINE") (100 . "AcDbEntity") (8 . "MASONRY") (62 . 7) (370 . 13) (100 . "AcDbLine") (10 7709.2760180995
2188.9140271493 0.0) (11 7479.2604751131 2188.9140271493 0.0))
((0 . "LINE") (100 . "AcDbEntity") (8 . "MASONRY") (62 . 7) (370 . 13) (100 . "AcDbLine") (10 7601.8099547511
2320.8127941176 0.0) (11 7485.5193438914 2320.8127941176 0.0))
((0 . "LINE") (100 . "AcDbEntity") (8 . "MASONRY") (62 . 7) (370 . 13) (100 . "AcDbLine") (10 7485.5193438914
2320.8127941176 0.0) (11 7485.5193438914 2296.3800904977 0.0))
((0 . "LINE") (100 . "AcDbEntity") (8 . "MASONRY") (62 . 7) (370 . 13) (100 . "AcDbLine") (10 7490.0451923077
812.5167081448 0.0) (11 7490.0451923077 825.7918552036 0.0))
((0 . "LINE") (100 . "AcDbEntity") (8 . "MASONRY") (62 . 7) (370 . 13) (100 . "AcDbLine") (10 7492.4582918552
2775.2637217195 0.0) (11 7492.4582918552 2786.575938914 0.0))
((0 . "LINE") (100 . "AcDbEntity") (8 . "MASONRY") (62 . 7) (370 . 13) (100 . "AcDbLine") (10 7492.4582918552
2775.2637217195 0.0) (11 7511.3122171946 2775.2637217195 0.0))
((0 . "LINE") (100 . "AcDbEntity") (8 . "MASONRY") (62 . 7) (370 . 13) (100 . "AcDbLine") (10 7492.4582918552
1742.0814479638 0.0) (11 7492.4582918552 1809.9547511312 0.0))
((0 . "LINE") (100 . "AcDbEntity") (8 . "MASONRY") (62 . 7) (370 . 13) (100 . "AcDbLine") (10 7492.4582918552
1161.3885520362 0.0) (11 7526.3949434389 1161.3885520362 0.0))
((0 . "LINE") (100 . "AcDbEntity") (8 . "MASONRY") (62 . 7) (370 . 13) (100 . "AcDbLine") (10 7492.4582918552
1161.3885520362 0.0) (11 7492.4582918552 1153.8461538462 0.0))
((0 . "LINE") (100 . "AcDbEntity") (8 . "MASONRY") (62 . 7) (370 . 13) (100 . "AcDbLine") (10 7498.1150904977
3152.3380882353 0.0) (11 7498.1150904977 3159.8791063348 0.0))
((0 . "LINE") (100 . "AcDbEntity") (8 . "MASONRY") (62 . 7) (370 . 13) (100 . "AcDbLine") (10 7492.4582918552
1742.0814479638 0.0) (11 7567.8698529412 1742.0814479638 0.0))
((0 . "LINE") (100 . "AcDbEntity") (8 . "MASONRY") (62 . 7) (370 . 13) (100 . "AcDbLine") (10 7567.8698529412
1742.0814479638 0.0) (11 7567.8698529412 1723.2268325792 0.0))
((0 . "LINE") (100 . "AcDbEntity") (8 . "MASONRY") (62 . 7) (370 . 13) (100 . "AcDbLine") (10 7500 1104.8274660633 0.0)
(11 7500 1119.9095022624 0.0))
((0 . "LINE") (100 . "AcDbEntity") (8 . "MASONRY") (62 . 7) (370 . 13) (100 . "AcDbLine") (10 7500 1104.8274660633 0.0)
(11 7628.2042081448 1104.8274660633 0.0))
((0 . "LINE") (100 . "AcDbEntity") (8 . "MASONRY") (62 . 7) (370 . 13) (100 . "AcDbLine") (10 7530.1661425339
903.0924660633 0.0) (11 7507.5417081448 903.0924660633 0.0))
((0 . "LINE") (100 . "AcDbEntity") (8 . "MASONRY") (62 . 7) (370 . 13) (100 . "AcDbLine") (10 7511.3122171946
1035.0678733032 0.0) (11 7571.6438122172 1035.0678733032 0.0))
((0 . "LINE") (100 . "AcDbEntity") (8 . "MASONRY") (62 . 7) (370 . 13) (100 . "AcDbLine") (10 7633.7802262443
595.8888574661 0.0) (11 7633.7802262443 640.8422171946 0.0))
((0 . "LINE") (100 . "AcDbEntity") (8 . "MASONRY") (62 . 7) (370 . 13) (100 . "AcDbLine") (10 7633.7802262443
640.8422171946 0.0) (11 7624.4343891403 640.8422171946 0.0))
((0 . "LINE") (100 . "AcDbEntity") (8 . "MASONRY") (62 . 7) (370 . 13) (100 . "AcDbLine") (10 7526.3949434389
2775.2637217195 0.0) (11 7652.3738574661 2775.2637217195 0.0))
((0 . "LINE") (100 . "AcDbEntity") (8 . "MASONRY") (62 . 7) (370 . 13) (100 . "AcDbLine") (10 7645.1739140272
727.751719457 0.0) (11 7624.4343891403 727.751719457 0.0))
((0 . "LINE") (100 . "AcDbEntity") (8 . "MASONRY") (62 . 7) (370 . 13) (100 . "AcDbLine") (10 7557.8718778281
729.5800113122 0.0) (11 7526.3949434389 729.5800113122 0.0))
((0 . "LINE") (100 . "AcDbEntity") (8 . "MASONRY") (62 . 7) (370 . 13) (100 . "AcDbLine") (10 7533.9366515837
1862.7453280543 0.0) (11 7601.8099547511 1862.7453280543 0.0))
((0 . "LINE") (100 . "AcDbEntity") (8 . "MASONRY") (62 . 7) (370 . 13) (100 . "AcDbLine") (10 7537.7071606335
2268.0995475113 0.0) (11 7688.5378733032 2268.0995475113 0.0))
((0 . "LINE") (100 . "AcDbEntity") (8 . "MASONRY") (62 . 7) (370 . 13) (100 . "AcDbLine") (10 7537.7071606335
1163.2734615385 0.0) (11 7586.727918552 1163.2734615385 0.0))
((0 . "LINE") (100 . "AcDbEntity") (8 . "MASONRY") (62 . 7) (370 . 13) (100 . "AcDbLine") (10 7703.6199095023
1813.7245701357 0.0) (11 7541.4783597285 1813.7245701357 0.0))
((0 . "LINE") (100 . "AcDbEntity") (8 . "MASONRY") (62 . 7) (370 . 13) (100 . "AcDbLine") (10 7550.9049773756
901.2075565611 0.0) (11 7550.9049773756 893.665158371 0.0))
((0 . "LINE") (100 . "AcDbEntity") (8 . "MASONRY") (62 . 7) (370 . 13) (100 . "AcDbLine") (10 7549.0193778281
822.0220361991 0.0) (11 7615.0978959276 822.0220361991 0.0))
((0 . "LINE") (100 . "AcDbEntity") (8 . "MASONRY") (62 . 7) (370 . 13) (100 . "AcDbLine") (10 7624.4343891403
822.0220361991 0.0) (11 7673.4530769231 822.0220361991 0.0))
((0 . "LINE") (100 . "AcDbEntity") (8 . "MASONRY") (62 . 7) (370 . 13) (100 . "AcDbLine") (10 7560.3315950226
2846.9082239819 0.0) (11 7560.3315950226 2854.4492420814 0.0))
((0 . "LINE") (100 . "AcDbEntity") (8 . "MASONRY") (62 . 7) (370 . 13) (100 . "AcDbLine") (10 7562.2171945701
2824.2837895928 0.0) (11 7562.2171945701 2816.742081448 0.0))
((0 . "LINE") (100 . "AcDbEntity") (8 . "MASONRY") (62 . 7) (370 . 13) (100 . "AcDbLine") (10 7565.9877036199
1617.6470588235 0.0) (11 7565.9877036199 1644.0413122172 0.0))
((0 . "LINE") (100 . "AcDbEntity") (8 . "MASONRY") (62 . 7) (370 . 13) (100 . "AcDbLine") (10 7865.7607692308
3105.2036199095 0.0) (11 7564.1027941176 3105.2036199095 0.0))
((0 . "LINE") (100 . "AcDbEntity") (8 . "MASONRY") (62 . 7) (370 . 13) (100 . "AcDbLine") (10 7861.9909502262
1674.2854751131 0.0) (11 7577.2992307692 1674.2854751131 0.0))
((0 . "LINE") (100 . "AcDbEntity") (8 . "MASONRY") (62 . 7) (370 . 13) (100 . "AcDbLine") (10 7577.2992307692
1674.2854751131 0.0) (11 7577.2992307692 1708.1447963801 0.0))
((0 . "LINE") (100 . "AcDbEntity") (8 . "MASONRY") (62 . 7) (370 . 13) (100 . "AcDbLine") (10 7571.6438122172
1006.7873303167 0.0) (11 7571.6438122172 1035.0678733032 0.0))
((0 . "LINE") (100 . "AcDbEntity") (8 . "MASONRY") (62 . 7) (370 . 13) (100 . "AcDbLine") (10 7571.6438122172
1035.0678733032 0.0) (11 7635.7466063348 1035.0678733032 0.0))
((0 . "LINE") (100 . "AcDbEntity") (8 . "MASONRY") (62 . 7) (370 . 13) (100 . "AcDbLine") (10 7635.7466063348
1035.0678733032 0.0) (11 7861.9909502262 1035.0678733032 0.0))
((0 . "LINE") (100 . "AcDbEntity") (8 . "MASONRY") (62 . 7) (370 . 13) (100 . "AcDbLine") (10 7577.3006108597
867.2709049774 0.0) (11 7577.3006108597 920.0594117647 0.0))
((0 . "LINE") (100 . "AcDbEntity") (8 . "MASONRY") (62 . 7) (370 . 13) (100 . "AcDbLine") (10 7579.185520362
959.6535520362 0.0) (11 7835.5966968326 959.6535520362 0.0))
((0 . "LINE") (100 . "AcDbEntity") (8 . "MASONRY") (62 . 7) (370 . 13) (100 . "AcDbLine") (10 7599.9236651584
2450.9806221719 0.0) (11 7599.9236651584 2428.3561877828 0.0))
((0 . "LINE") (100 . "AcDbEntity") (8 . "MASONRY") (62 . 7) (370 . 13) (100 . "AcDbLine") (10 7639.5164253394
2428.3561877828 0.0) (11 7599.9236651584 2428.3561877828 0.0))
((0 . "LINE") (100 . "AcDbEntity") (8 . "MASONRY") (62 . 7) (370 . 13) (100 . "AcDbLine") (10 7861.9909502262
2971.3426131222 0.0) (11 7609.3523529412 2971.3426131222 0.0))
((0 . "LINE") (100 . "AcDbEntity") (8 . "MASONRY") (62 . 7) (370 . 13) (100 . "AcDbLine") (10 7620.6645701357
2552.7905769231 0.0) (11 7613.1221719457 2552.7905769231 0.0))
((0 . "LINE") (100 . "AcDbEntity") (8 . "MASONRY") (62 . 7) (370 . 13) (100 . "AcDbLine") (10 7618.778280543
2605.5804638009 0.0) (11 7618.778280543 2633.8616968326 0.0))
((0 . "LINE") (100 . "AcDbEntity") (8 . "MASONRY") (62 . 7) (370 . 13) (100 . "AcDbLine") (10 7648.9437330317
2633.8616968326 0.0) (11 7618.778280543 2633.8616968326 0.0))
((0 . "LINE") (100 . "AcDbEntity") (8 . "MASONRY") (62 . 7) (370 . 13) (100 . "AcDbLine") (10 7865.7607692308
1591.2514253394 0.0) (11 7616.8919909502 1591.2514253394 0.0))
((0 . "LINE") (100 . "AcDbEntity") (8 . "MASONRY") (62 . 7) (370 . 13) (100 . "AcDbLine") (10 7616.8919909502
1263.1985067873 0.0) (11 7641.4027149321 1263.1985067873 0.0))
((0 . "LINE") (100 . "AcDbEntity") (8 . "MASONRY") (62 . 7) (370 . 13) (100 . "AcDbLine") (10 7620.6645701357
1540.3464479638 0.0) (11 7631.9767873303 1540.3464479638 0.0))
((0 . "LINE") (100 . "AcDbEntity") (8 . "MASONRY") (62 . 7) (370 . 13) (100 . "AcDbLine") (10 7620.6645701357
1474.3580542986 0.0) (11 7699.8500904977 1474.3580542986 0.0))
((0 . "LINE") (100 . "AcDbEntity") (8 . "MASONRY") (62 . 7) (370 . 13) (100 . "AcDbLine") (10 7624.4343891403
1742.0814479638 0.0) (11 7688.5378733032 1742.0814479638 0.0))
((0 . "LINE") (100 . "AcDbEntity") (8 . "MASONRY") (62 . 7) (370 . 13) (100 . "AcDbLine") (10 7628.2042081448
1244.3438914027 0.0) (11 7641.4027149321 1244.3438914027 0.0))
((0 . "LINE") (100 . "AcDbEntity") (8 . "MASONRY") (62 . 7) (370 . 13) (100 . "AcDbLine") (10 7628.2042081448
1134.9915384615 0.0) (11 7628.2042081448 1104.8274660633 0.0))
((0 . "LINE") (100 . "AcDbEntity") (8 . "MASONRY") (62 . 7) (370 . 13) (100 . "AcDbLine") (10 7628.2042081448
1070.8908144796 0.0) (11 7628.2042081448 1104.8274660633 0.0))
((0 . "LINE") (100 . "AcDbEntity") (8 . "MASONRY") (62 . 7) (370 . 13) (100 . "AcDbLine") (10 7631.9767873303
2586.7272285068 0.0) (11 7822.3981900452 2586.7272285068 0.0))
((0 . "LINE") (100 . "AcDbEntity") (8 . "MASONRY") (62 . 7) (370 . 13) (100 . "AcDbLine") (10 7633.8616968326
2077.6774547511 0.0) (11 7633.8616968326 2111.6141063348 0.0))
((0 . "LINE") (100 . "AcDbEntity") (8 . "MASONRY") (62 . 7) (370 . 13) (100 . "AcDbLine") (10 7633.8616968326
2111.6141063348 0.0) (11 7861.9909502262 2111.6141063348 0.0))
((0 . "LINE") (100 . "AcDbEntity") (8 . "MASONRY") (62 . 7) (370 . 13) (100 . "AcDbLine") (10 7639.5164253394
2009.8041515837 0.0) (11 7639.5164253394 2032.4285859729 0.0))
((0 . "LINE") (100 . "AcDbEntity") (8 . "MASONRY") (62 . 7) (370 . 13) (100 . "AcDbLine") (10 7865.7607692308
1163.2734615385 0.0) (11 7631.9767873303 1163.2734615385 0.0))
((0 . "LINE") (100 . "AcDbEntity") (8 . "MASONRY") (62 . 7) (370 . 13) (100 . "AcDbLine") (10 7805.4298642534
3529.4117647059 0.0) (11 7635.7466063348 3529.4117647059 0.0))
((0 . "LINE") (100 . "AcDbEntity") (8 . "MASONRY") (62 . 7) (370 . 13) (100 . "AcDbLine") (10 7639.5164253394
2371.79510181 0.0) (11 7639.5164253394 2401.9605542986 0.0))
((0 . "LINE") (100 . "AcDbEntity") (8 . "MASONRY") (62 . 7) (370 . 13) (100 . "AcDbLine") (10 7641.4027149321
1263.1985067873 0.0) (11 7641.4027149321 1244.3438914027 0.0))
((0 . "LINE") (100 . "AcDbEntity") (8 . "MASONRY") (62 . 7) (370 . 13) (100 . "AcDbLine") (10 7641.4027149321
1263.1985067873 0.0) (11 7641.4027149321 1297.135158371 0.0))
((0 . "LINE") (100 . "AcDbEntity") (8 . "MASONRY") (62 . 7) (370 . 13) (100 . "AcDbLine") (10 7639.5164253394
2428.3561877828 0.0) (11 7639.5164253394 2401.9605542986 0.0))
((0 . "LINE") (100 . "AcDbEntity") (8 . "MASONRY") (62 . 7) (370 . 13) (100 . "AcDbLine") (10 7639.5164253394
2428.3561877828 0.0) (11 7692.3035520362 2428.3561877828 0.0))
((0 . "LINE") (100 . "AcDbEntity") (8 . "MASONRY") (62 . 7) (370 . 13) (100 . "AcDbLine") (10 7692.3035520362
2428.3561877828 0.0) (11 7692.3035520362 2401.9605542986 0.0))
((0 . "LINE") (100 . "AcDbEntity") (8 . "MASONRY") (62 . 7) (370 . 13) (100 . "AcDbLine") (10 7861.9909502262
2322.8530542986 0.0) (11 7645.1725339367 2322.8530542986 0.0))
((0 . "LINE") (100 . "AcDbEntity") (8 . "MASONRY") (62 . 7) (370 . 13) (100 . "AcDbLine") (10 7645.1725339367
2322.8530542986 0.0) (11 7645.1725339367 2352.9411764706 0.0))
((0 . "LINE") (100 . "AcDbEntity") (8 . "MASONRY") (62 . 7) (370 . 13) (100 . "AcDbLine") (10 7639.5164253394
2009.8041515837 0.0) (11 7639.5164253394 1990.9502262443 0.0))
((0 . "LINE") (100 . "AcDbEntity") (8 . "MASONRY") (62 . 7) (370 . 13) (100 . "AcDbLine") (10 7639.5164253394
1864.6302375566 0.0) (11 7707.3897285068 1864.6302375566 0.0))
((0 . "LINE") (100 . "AcDbEntity") (8 . "MASONRY") (62 . 7) (370 . 13) (100 . "AcDbLine") (10 7641.4027149321
1297.135158371 0.0) (11 7641.4027149321 1308.4473755656 0.0))
((0 . "LINE") (100 . "AcDbEntity") (8 . "MASONRY") (62 . 7) (370 . 13) (100 . "AcDbLine") (10 7641.4027149321
1229.2618552036 0.0) (11 7641.4027149321 1244.3438914027 0.0))
((0 . "LINE") (100 . "AcDbEntity") (8 . "MASONRY") (62 . 7) (370 . 13) (100 . "AcDbLine") (10 7639.5164253394
2401.9605542986 0.0) (11 7692.3035520362 2401.9605542986 0.0))
((0 . "LINE") (100 . "AcDbEntity") (8 . "MASONRY") (62 . 7) (370 . 13) (100 . "AcDbLine") (10 7639.5164253394
2009.8041515837 0.0) (11 7865.7607692308 2009.8041515837 0.0))
((0 . "LINE") (100 . "AcDbEntity") (8 . "MASONRY") (62 . 7) (370 . 13) (100 . "AcDbLine") (10 7641.4027149321
1297.135158371 0.0) (11 7688.5378733032 1297.135158371 0.0))
((0 . "LINE") (100 . "AcDbEntity") (8 . "MASONRY") (62 . 7) (370 . 13) (100 . "AcDbLine") (10 7641.4027149321
1199.0950226244 0.0) (11 7641.4027149321 1229.2618552036 0.0))
((0 . "LINE") (100 . "AcDbEntity") (8 . "MASONRY") (62 . 7) (370 . 13) (100 . "AcDbLine") (10 7645.1739140272
727.751719457 0.0) (11 7645.1739140272 701.3574660633 0.0))
((0 . "LINE") (100 . "AcDbEntity") (8 . "MASONRY") (62 . 7) (370 . 13) (100 . "AcDbLine") (10 7645.1739140272
727.751719457 0.0) (11 7861.9909502262 727.751719457 0.0))
((0 . "LINE") (100 . "AcDbEntity") (8 . "MASONRY") (62 . 7) (370 . 13) (100 . "AcDbLine") (10 7647.0588235294
3416.2895927602 0.0) (11 7647.0588235294 3423.831300905 0.0))
((0 . "LINE") (100 . "AcDbEntity") (8 . "MASONRY") (62 . 7) (370 . 13) (100 . "AcDbLine") (10 7647.0588235294
3391.7795588235 0.0) (11 7699.8500904977 3391.7795588235 0.0))
((0 . "LINE") (100 . "AcDbEntity") (8 . "MASONRY") (62 . 7) (370 . 13) (100 . "AcDbLine") (10 7648.9437330317
2633.8616968326 0.0) (11 7869.5333484163 2633.8616968326 0.0))
((0 . "LINE") (100 . "AcDbEntity") (8 . "MASONRY") (62 . 7) (370 . 13) (100 . "AcDbLine") (10 7648.9437330317
2633.8616968326 0.0) (11 7648.9437330317 2688.5371832579 0.0))
((0 . "LINE") (100 . "AcDbEntity") (8 . "MASONRY") (62 . 7) (370 . 13) (100 . "AcDbLine") (10 7641.4027149321
1229.2618552036 0.0) (11 7665.913438914 1229.2618552036 0.0))
((0 . "LINE") (100 . "AcDbEntity") (8 . "MASONRY") (62 . 7) (370 . 13) (100 . "AcDbLine") (10 7714.9321266968
2722.658178733 0.0) (11 7652.3738574661 2722.658178733 0.0))
((0 . "LINE") (100 . "AcDbEntity") (8 . "MASONRY") (62 . 7) (370 . 13) (100 . "AcDbLine") (10 7652.3738574661
2722.658178733 0.0) (11 7652.3738574661 2775.2637217195 0.0))
((0 . "LINE") (100 . "AcDbEntity") (8 . "MASONRY") (62 . 7) (370 . 13) (100 . "AcDbLine") (10 7865.7607692308
2775.2637217195 0.0) (11 7652.3738574661 2775.2637217195 0.0))
((0 . "LINE") (100 . "AcDbEntity") (8 . "MASONRY") (62 . 7) (370 . 13) (100 . "AcDbLine") (10 7669.6832579186
3046.7569343891 0.0) (11 7692.3076923077 3046.7569343891 0.0))
((0 . "LINE") (100 . "AcDbEntity") (8 . "MASONRY") (62 . 7) (370 . 13) (100 . "AcDbLine") (10 7711.1623076923
563.7259502262 0.0) (11 7677.2256561086 563.7259502262 0.0))
((0 . "LINE") (100 . "AcDbEntity") (8 . "MASONRY") (62 . 7) (370 . 13) (100 . "AcDbLine") (10 7865.7607692308
1231.1467647059 0.0) (11 7680.9954751131 1231.1467647059 0.0))
((0 . "LINE") (100 . "AcDbEntity") (8 . "MASONRY") (62 . 7) (370 . 13) (100 . "AcDbLine") (10 7692.3076923077
1547.8888461538 0.0) (11 7865.7607692308 1547.8888461538 0.0))
((0 . "LINE") (100 . "AcDbEntity") (8 . "MASONRY") (62 . 7) (370 . 13) (100 . "AcDbLine") (10 7696.0775113122
2458.5216402715 0.0) (11 7696.0775113122 2503.7705090498 0.0))
((0 . "LINE") (100 . "AcDbEntity") (8 . "MASONRY") (62 . 7) (370 . 13) (100 . "AcDbLine") (10 7696.0775113122
2503.7705090498 0.0) (11 7869.5333484163 2503.7705090498 0.0))
((0 . "LINE") (100 . "AcDbEntity") (8 . "MASONRY") (62 . 7) (370 . 13) (100 . "AcDbLine") (10 7730.0141628959
2401.9605542986 0.0) (11 7692.3035520362 2401.9605542986 0.0))
((0 . "LINE") (100 . "AcDbEntity") (8 . "MASONRY") (62 . 7) (370 . 13) (100 . "AcDbLine") (10 7709.2760180995
2188.9140271493 0.0) (11 7709.2760180995 2149.3212669683 0.0))
((0 . "LINE") (100 . "AcDbEntity") (8 . "MASONRY") (62 . 7) (370 . 13) (100 . "AcDbLine") (10 7709.2760180995
2188.9140271493 0.0) (11 7779.0356108597 2188.9140271493 0.0))
((0 . "LINE") (100 . "AcDbEntity") (8 . "MASONRY") (62 . 7) (370 . 13) (100 . "AcDbLine") (10 7869.5333484163
818.2494570136 0.0) (11 7854.4485520362 818.2494570136 0.0))
((0 . "LINE") (100 . "AcDbEntity") (8 . "MASONRY") (62 . 7) (370 . 13) (100 . "AcDbLine") (10 7854.4485520362
818.2494570136 0.0) (11 7707.3897285068 818.2494570136 0.0))
((0 . "LINE") (100 . "AcDbEntity") (8 . "MASONRY") (62 . 7) (370 . 13) (100 . "AcDbLine") (10 7865.7607692308
1334.8416289593 0.0) (11 7714.9321266968 1334.8416289593 0.0))
((0 . "LINE") (100 . "AcDbEntity") (8 . "MASONRY") (62 . 7) (370 . 13) (100 . "AcDbLine") (10 7722.4745248869
1300.9049773756 0.0) (11 7714.9321266968 1300.9049773756 0.0))
((0 . "LINE") (100 . "AcDbEntity") (8 . "MASONRY") (62 . 7) (370 . 13) (100 . "AcDbLine") (10 7865.7607692308
3042.9864253394 0.0) (11 7733.7867420814 3042.9864253394 0.0))
((0 . "LINE") (100 . "AcDbEntity") (8 . "MASONRY") (62 . 7) (370 . 13) (100 . "AcDbLine") (10 7750.7536877828
1828.8086764706 0.0) (11 7750.7536877828 1847.6619117647 0.0))
((0 . "LINE") (100 . "AcDbEntity") (8 . "MASONRY") (62 . 7) (370 . 13) (100 . "AcDbLine") (10 7750.7536877828
1811.8396606335 0.0) (11 7741.3263800905 1811.8396606335 0.0))
((0 . "LINE") (100 . "AcDbEntity") (8 . "MASONRY") (62 . 7) (370 . 13) (100 . "AcDbLine") (10 7745.098959276
2400.0749547511 0.0) (11 7861.9909502262 2400.0749547511 0.0))
((0 . "LINE") (100 . "AcDbEntity") (8 . "MASONRY") (62 . 7) (370 . 13) (100 . "AcDbLine") (10 7812.9722624434
642.9114705882 0.0) (11 7745.098959276 642.9114705882 0.0))
((0 . "LINE") (100 . "AcDbEntity") (8 . "MASONRY") (62 . 7) (370 . 13) (100 . "AcDbLine") (10 7750.7536877828
1806.1849321267 0.0) (11 7750.7536877828 1811.8396606335 0.0))
((0 . "LINE") (100 . "AcDbEntity") (8 . "MASONRY") (62 . 7) (370 . 13) (100 . "AcDbLine") (10 7750.7536877828
1828.8086764706 0.0) (11 7750.7536877828 1811.8396606335 0.0))
((0 . "LINE") (100 . "AcDbEntity") (8 . "MASONRY") (62 . 7) (370 . 13) (100 . "AcDbLine") (10 7750.7536877828
1828.8086764706 0.0) (11 7775.2630316742 1828.8086764706 0.0))
((0 . "LINE") (100 . "AcDbEntity") (8 . "MASONRY") (62 . 7) (370 . 13) (100 . "AcDbLine") (10 7869.5333484163
1753.3936651584 0.0) (11 7752.6385972851 1753.3936651584 0.0))
((0 . "LINE") (100 . "AcDbEntity") (8 . "MASONRY") (62 . 7) (370 . 13) (100 . "AcDbLine") (10 7769.6069230769
2288.8383823529 0.0) (11 7769.6069230769 2266.2139479638 0.0))
((0 . "LINE") (100 . "AcDbEntity") (8 . "MASONRY") (62 . 7) (370 . 13) (100 . "AcDbLine") (10 7763.9508144796
1953.2430656109 0.0) (11 7861.9909502262 1953.2430656109 0.0))
((0 . "LINE") (100 . "AcDbEntity") (8 . "MASONRY") (62 . 7) (370 . 13) (100 . "AcDbLine") (10 7767.7220135747
573.1532579186 0.0) (11 7767.7220135747 561.841040724 0.0))
((0 . "LINE") (100 . "AcDbEntity") (8 . "MASONRY") (62 . 7) (370 . 13) (100 . "AcDbLine") (10 7779.0356108597
2188.9140271493 0.0) (11 7779.0356108597 2239.8190045249 0.0))
((0 . "LINE") (100 . "AcDbEntity") (8 . "MASONRY") (62 . 7) (370 . 13) (100 . "AcDbLine") (10 7869.5333484163
2188.9140271493 0.0) (11 7779.0356108597 2188.9140271493 0.0))
((0 . "LINE") (100 . "AcDbEntity") (8 . "MASONRY") (62 . 7) (370 . 13) (100 . "AcDbLine") (10 7794.1176470588
2846.9082239819 0.0) (11 7794.1176470588 2830.0165384615 0.0))
((0 . "LINE") (100 . "AcDbEntity") (8 . "MASONRY") (62 . 7) (370 . 13) (100 . "AcDbLine") (10 7794.1176470588
2830.0165384615 0.0) (11 7869.5333484163 2830.0165384615 0.0))
((0 . "LINE") (100 . "AcDbEntity") (8 . "MASONRY") (62 . 7) (370 . 13) (100 . "AcDbLine") (10 7797.8874660633
1830.6942760181 0.0) (11 7865.7607692308 1830.6942760181 0.0))
((0 . "LINE") (100 . "AcDbEntity") (8 . "MASONRY") (62 . 7) (370 . 13) (100 . "AcDbLine") (10 7822.3981900452
2586.7272285068 0.0) (11 7822.3981900452 2567.8733031674 0.0))
((0 . "LINE") (100 . "AcDbEntity") (8 . "MASONRY") (62 . 7) (370 . 13) (100 . "AcDbLine") (10 7820.5119004525
563.7259502262 0.0) (11 7858.2211312217 563.7259502262 0.0))
((0 . "LINE") (100 . "AcDbEntity") (8 . "MASONRY") (62 . 7) (370 . 13) (100 . "AcDbLine") (10 7861.9909502262
2586.7272285068 0.0) (11 7822.3981900452 2586.7272285068 0.0))
((0 . "LINE") (100 . "AcDbEntity") (8 . "MASONRY") (62 . 7) (370 . 13) (100 . "AcDbLine") (10 7846.9089140271
955.8823529412 0.0) (11 7861.9909502262 955.8823529412 0.0))
((0 . "LINE") (100 . "AcDbEntity") (8 . "MASONRY") (62 . 7) (370 . 13) (100 . "AcDbLine") (10 9592.7601809955
5539.2152262443 0.0) (11 9592.7601809955 5512.8209728507 0.0))
((0 . "LINE") (100 . "AcDbEntity") (8 . "MASONRY") (62 . 7) (370 . 13) (100 . "AcDbLine") (10 9884.9155882353
5248.8687782805 0.0) (11 9611.6147963801 5248.8687782805 0.0))
((0 . "LINE") (100 . "AcDbEntity") (8 . "MASONRY") (62 . 7) (370 . 13) (100 . "AcDbLine") (10 9611.6147963801
5248.8687782805 0.0) (11 9592.7601809955 5248.8687782805 0.0))
((0 . "LINE") (100 . "AcDbEntity") (8 . "MASONRY") (62 . 7) (370 . 13) (100 . "AcDbLine") (10 9715.3096606335
2771.4932126697 0.0) (11 9592.7601809955 2771.4932126697 0.0))
((0 . "LINE") (100 . "AcDbEntity") (8 . "MASONRY") (62 . 7) (370 . 13) (100 . "AcDbLine") (10 9753.0161312217
1987.1797171946 0.0) (11 9592.7601809955 1987.1797171946 0.0))
((0 . "LINE") (100 . "AcDbEntity") (8 . "MASONRY") (62 . 7) (370 . 13) (100 . "AcDbLine") (10 9792.6102714932
776.9264479638 0.0) (11 9758.6660294118 776.9264479638 0.0))
((0 . "LINE") (100 . "AcDbEntity") (8 . "MASONRY") (62 . 7) (370 . 13) (100 . "AcDbLine") (10 9758.6660294118
776.9264479638 0.0) (11 9592.7601809955 776.9264479638 0.0))
((0 . "LINE") (100 . "AcDbEntity") (8 . "MASONRY") (62 . 7) (370 . 13) (100 . "AcDbLine") (10 9592.7601809955
424.2081447964 0.0) (11 9856.7109954751 424.2081447964 0.0))
((0 . "LINE") (100 . "AcDbEntity") (8 . "MASONRY") (62 . 7) (370 . 13) (100 . "AcDbLine") (10 10005.6561085973
6391.4027149321 0.0) (11 9596.53 6391.4027149321 0.0))
((0 . "LINE") (100 . "AcDbEntity") (8 . "MASONRY") (62 . 7) (370 . 13) (100 . "AcDbLine") (10 9596.53 6202.8658823529
0.0) (11 9639.893959276 6202.8658823529 0.0))
((0 . "LINE") (100 . "AcDbEntity") (8 . "MASONRY") (62 . 7) (370 . 13) (100 . "AcDbLine") (10 9596.53 6104.7525565611
0.0) (11 9639.2918891403 6104.7525565611 0.0))
((0 . "LINE") (100 . "AcDbEntity") (8 . "MASONRY") (62 . 7) (370 . 13) (100 . "AcDbLine") (10 9639.2918891403
6104.7525565611 0.0) (11 9639.2918891403 6063.3484162896 0.0))
((0 . "LINE") (100 . "AcDbEntity") (8 . "MASONRY") (62 . 7) (370 . 13) (100 . "AcDbLine") (10 9596.53 6063.3484162896
0.0) (11 9639.2918891403 6063.3484162896 0.0))
((0 . "LINE") (100 . "AcDbEntity") (8 . "MASONRY") (62 . 7) (370 . 13) (100 . "AcDbLine") (10 9596.53 5953.9971040724
0.0) (11 9719.079479638 5953.9971040724 0.0))
((0 . "LINE") (100 . "AcDbEntity") (8 . "MASONRY") (62 . 7) (370 . 13) (100 . "AcDbLine") (10 9596.53 5793.7408031674
0.0) (11 9604.07239819 5793.7408031674 0.0))
((0 . "LINE") (100 . "AcDbEntity") (8 . "MASONRY") (62 . 7) (370 . 13) (100 . "AcDbLine") (10 9596.53 5109.3509728507
0.0) (11 9638.0090497738 5109.3509728507 0.0))
((0 . "LINE") (100 . "AcDbEntity") (8 . "MASONRY") (62 . 7) (370 . 13) (100 . "AcDbLine") (10 9615.3846153846
4775.6412556561 0.0) (11 9596.53 4775.6412556561 0.0))
((0 . "LINE") (100 . "AcDbEntity") (8 . "MASONRY") (62 . 7) (370 . 13) (100 . "AcDbLine") (10 9639.8953393665
3989.4414705882 0.0) (11 9596.53 3989.4414705882 0.0))
((0 . "LINE") (100 . "AcDbEntity") (8 . "MASONRY") (62 . 7) (370 . 13) (100 . "AcDbLine") (10 9596.53 3951.735 0.0) (11
9596.53 3959.2760180995 0.0))
((0 . "LINE") (100 . "AcDbEntity") (8 . "MASONRY") (62 . 7) (370 . 13) (100 . "AcDbLine") (10 9845.3987782805
3740.5726923077 0.0) (11 9596.53 3740.5726923077 0.0))
((0 . "LINE") (100 . "AcDbEntity") (8 . "MASONRY") (62 . 7) (370 . 13) (100 . "AcDbLine") (10 9630.4666515837
3555.8067081448 0.0) (11 9596.53 3555.8067081448 0.0))
((0 . "LINE") (100 . "AcDbEntity") (8 . "MASONRY") (62 . 7) (370 . 13) (100 . "AcDbLine") (10 9596.53 3472.850678733
0.0) (11 10111.2358823529 3472.850678733 0.0))
((0 . "LINE") (100 . "AcDbEntity") (8 . "MASONRY") (62 . 7) (370 . 13) (100 . "AcDbLine") (10 9596.53 3099.5475113122
0.0) (11 9860.4835746606 3099.5475113122 0.0))
((0 . "LINE") (100 . "AcDbEntity") (8 . "MASONRY") (62 . 7) (370 . 13) (100 . "AcDbLine") (10 9596.53 2518.8539253394
0.0) (11 9622.9270135747 2518.8539253394 0.0))
((0 . "LINE") (100 . "AcDbEntity") (8 . "MASONRY") (62 . 7) (370 . 13) (100 . "AcDbLine") (10 9607.8422171946
2454.7511312217 0.0) (11 9596.53 2454.7511312217 0.0))
((0 . "LINE") (100 . "AcDbEntity") (8 . "MASONRY") (62 . 7) (370 . 13) (100 . "AcDbLine") (10 9596.53 1262.5964366516
0.0) (11 9632.348800905 1262.5964366516 0.0))
((0 . "LINE") (100 . "AcDbEntity") (8 . "MASONRY") (62 . 7) (370 . 13) (100 . "AcDbLine") (10 9632.348800905
1262.5964366516 0.0) (11 9632.348800905 1240.5740723982 0.0))
((0 . "LINE") (100 . "AcDbEntity") (8 . "MASONRY") (62 . 7) (370 . 13) (100 . "AcDbLine") (10 9781.2966742081
354.4485520362 0.0) (11 9596.53 354.4485520362 0.0))
((0 . "LINE") (100 . "AcDbEntity") (8 . "MASONRY") (62 . 7) (370 . 13) (100 . "AcDbLine") (10 9638.0090497738
177.2256561086 0.0) (11 9596.53 177.2256561086 0.0))
((0 . "LINE") (100 . "AcDbEntity") (8 . "MASONRY") (62 . 7) (370 . 13) (100 . "AcDbLine") (10 9679.4880995475
5331.8248076923 0.0) (11 9600.3025791855 5331.8248076923 0.0))
((0 . "LINE") (100 . "AcDbEntity") (8 . "MASONRY") (62 . 7) (370 . 13) (100 . "AcDbLine") (10 9600.3025791855
5003.771199095 0.0) (11 9653.0910859729 5003.771199095 0.0))
((0 . "LINE") (100 . "AcDbEntity") (8 . "MASONRY") (62 . 7) (370 . 13) (100 . "AcDbLine") (10 9615.3846153846
4724.7355882353 0.0) (11 9600.3025791855 4724.7355882353 0.0))
((0 . "LINE") (100 . "AcDbEntity") (8 . "MASONRY") (62 . 7) (370 . 13) (100 . "AcDbLine") (10 9626.6968325792
4596.5313800905 0.0) (11 9600.3025791855 4596.5313800905 0.0))
((0 . "LINE") (100 . "AcDbEntity") (8 . "MASONRY") (62 . 7) (370 . 13) (100 . "AcDbLine") (10 9600.3025791855
4102.5636425339 0.0) (11 9600.3025791855 4096.9082239819 0.0))
((0 . "LINE") (100 . "AcDbEntity") (8 . "MASONRY") (62 . 7) (370 . 13) (100 . "AcDbLine") (10 9600.3025791855
4087.4816063348 0.0) (11 9600.3025791855 4096.9082239819 0.0))
((0 . "LINE") (100 . "AcDbEntity") (8 . "MASONRY") (62 . 7) (370 . 13) (100 . "AcDbLine") (10 9600.3025791855
4068.6269909502 0.0) (11 9717.1945701357 4068.6269909502 0.0))
((0 . "LINE") (100 . "AcDbEntity") (8 . "MASONRY") (62 . 7) (370 . 13) (100 . "AcDbLine") (10 9600.3025791855
3684.0116063348 0.0) (11 9630.4666515837 3684.0116063348 0.0))
((0 . "LINE") (100 . "AcDbEntity") (8 . "MASONRY") (62 . 7) (370 . 13) (100 . "AcDbLine") (10 9630.4666515837
3597.2850678733 0.0) (11 9600.3025791855 3597.2850678733 0.0))
((0 . "LINE") (100 . "AcDbEntity") (8 . "MASONRY") (62 . 7) (370 . 13) (100 . "AcDbLine") (10 9600.3025791855
3190.0452488688 0.0) (11 9862.3671040724 3190.0452488688 0.0))
((0 . "LINE") (100 . "AcDbEntity") (8 . "MASONRY") (62 . 7) (370 . 13) (100 . "AcDbLine") (10 9739.8190045249
2941.1764705882 0.0) (11 9600.3025791855 2941.1764705882 0.0))
((0 . "LINE") (100 . "AcDbEntity") (8 . "MASONRY") (62 . 7) (370 . 13) (100 . "AcDbLine") (10 9626.0947624434
2741.3270701357 0.0) (11 9626.0947624434 2720.5882352941 0.0))
((0 . "LINE") (100 . "AcDbEntity") (8 . "MASONRY") (62 . 7) (370 . 13) (100 . "AcDbLine") (10 9626.0947624434
2720.5882352941 0.0) (11 9600.3025791855 2720.5882352941 0.0))
((0 . "LINE") (100 . "AcDbEntity") (8 . "MASONRY") (62 . 7) (370 . 13) (100 . "AcDbLine") (10 9841.628959276
2405.7317533937 0.0) (11 9600.3025791855 2405.7317533937 0.0))
((0 . "LINE") (100 . "AcDbEntity") (8 . "MASONRY") (62 . 7) (370 . 13) (100 . "AcDbLine") (10 9600.3025791855
2313.3484162896 0.0) (11 9668.1758823529 2313.3484162896 0.0))
((0 . "LINE") (100 . "AcDbEntity") (8 . "MASONRY") (62 . 7) (370 . 13) (100 . "AcDbLine") (10 9687.0291176471
2237.9340950226 0.0) (11 9600.3025791855 2237.9340950226 0.0))
((0 . "LINE") (100 . "AcDbEntity") (8 . "MASONRY") (62 . 7) (370 . 13) (100 . "AcDbLine") (10 9653.0910859729
1858.9741289593 0.0) (11 9600.3025791855 1858.9741289593 0.0))
((0 . "LINE") (100 . "AcDbEntity") (8 . "MASONRY") (62 . 7) (370 . 13) (100 . "AcDbLine") (10 9600.3025791855
1613.877239819 0.0) (11 9719.079479638 1613.877239819 0.0))
((0 . "LINE") (100 . "AcDbEntity") (8 . "MASONRY") (62 . 7) (370 . 13) (100 . "AcDbLine") (10 9600.3025791855
1340.4977375566 0.0) (11 9694.5701357466 1340.4977375566 0.0))
((0 . "LINE") (100 . "AcDbEntity") (8 . "MASONRY") (62 . 7) (370 . 13) (100 . "AcDbLine") (10 9626.6968325792
1176.4705882353 0.0) (11 9600.3025791855 1176.4705882353 0.0))
((0 . "LINE") (100 . "AcDbEntity") (8 . "MASONRY") (62 . 7) (370 . 13) (100 . "AcDbLine") (10 9671.9457013575
991.7052941176 0.0) (11 9600.3025791855 991.7052941176 0.0))
((0 . "LINE") (100 . "AcDbEntity") (8 . "MASONRY") (62 . 7) (370 . 13) (100 . "AcDbLine") (10 9679.4880995475
852.1874886878 0.0) (11 9600.3025791855 852.1874886878 0.0))
((0 . "LINE") (100 . "AcDbEntity") (8 . "MASONRY") (62 . 7) (370 . 13) (100 . "AcDbLine") (10 9647.4363574661
720.212081448 0.0) (11 9600.3025791855 720.212081448 0.0))
((0 . "LINE") (100 . "AcDbEntity") (8 . "MASONRY") (62 . 7) (370 . 13) (100 . "AcDbLine") (10 9600.3025791855
595.7776923077 0.0) (11 9607.8422171946 595.7776923077 0.0))
((0 . "LINE") (100 . "AcDbEntity") (8 . "MASONRY") (62 . 7) (370 . 13) (100 . "AcDbLine") (10 9762.443438914
539.2166063348 0.0) (11 9600.3025791855 539.2166063348 0.0))
((0 . "LINE") (100 . "AcDbEntity") (8 . "MASONRY") (62 . 7) (370 . 13) (100 . "AcDbLine") (10 9600.3025791855
246.9838687783 0.0) (11 9607.8422171946 246.9838687783 0.0))
((0 . "LINE") (100 . "AcDbEntity") (8 . "MASONRY") (62 . 7) (370 . 13) (100 . "AcDbLine") (10 9894.4202262443
82.956719457 0.0) (11 9600.3025791855 82.956719457 0.0))
((0 . "LINE") (100 . "AcDbEntity") (8 . "MASONRY") (62 . 7) (370 . 13) (100 . "AcDbLine") (10 9622.9270135747
5712.6696832579 0.0) (11 9604.07239819 5712.6696832579 0.0))
((0 . "LINE") (100 . "AcDbEntity") (8 . "MASONRY") (62 . 7) (370 . 13) (100 . "AcDbLine") (10 9604.07239819
5678.7330316742 0.0) (11 9622.9270135747 5678.7330316742 0.0))
((0 . "LINE") (100 . "AcDbEntity") (8 . "MASONRY") (62 . 7) (370 . 13) (100 . "AcDbLine") (10 9604.07239819
5446.8325791855 0.0) (11 9664.4033031674 5446.8325791855 0.0))
((0 . "LINE") (100 . "AcDbEntity") (8 . "MASONRY") (62 . 7) (370 . 13) (100 . "AcDbLine") (10 9638.0090497738
5135.5919457014 0.0) (11 9604.07239819 5135.5919457014 0.0))
((0 . "LINE") (100 . "AcDbEntity") (8 . "MASONRY") (62 . 7) (370 . 13) (100 . "AcDbLine") (10 9798.2615497738
4892.5339366516 0.0) (11 9604.07239819 4892.5339366516 0.0))
((0 . "LINE") (100 . "AcDbEntity") (8 . "MASONRY") (62 . 7) (370 . 13) (100 . "AcDbLine") (10 10118.778280543
4517.3458597285 0.0) (11 9604.07239819 4517.3458597285 0.0))
((0 . "LINE") (100 . "AcDbEntity") (8 . "MASONRY") (62 . 7) (370 . 13) (100 . "AcDbLine") (10 9798.265 4411.7647058824
0.0) (11 9604.07239819 4411.7647058824 0.0))
((0 . "LINE") (100 . "AcDbEntity") (8 . "MASONRY") (62 . 7) (370 . 13) (100 . "AcDbLine") (10 9604.07239819
4340.0435633484 0.0) (11 9720.9595588235 4340.0435633484 0.0))
((0 . "LINE") (100 . "AcDbEntity") (8 . "MASONRY") (62 . 7) (370 . 13) (100 . "AcDbLine") (10 9720.9595588235
4340.0435633484 0.0) (11 9739.8190045249 4340.0435633484 0.0))
((0 . "LINE") (100 . "AcDbEntity") (8 . "MASONRY") (62 . 7) (370 . 13) (100 . "AcDbLine") (10 9739.8190045249
4340.0435633484 0.0) (11 9866.1383031674 4340.0435633484 0.0))
((0 . "LINE") (100 . "AcDbEntity") (8 . "MASONRY") (62 . 7) (370 . 13) (100 . "AcDbLine") (10 9866.1383031674
4193.0613800905 0.0) (11 9604.07239819 4193.0613800905 0.0))
((0 . "LINE") (100 . "AcDbEntity") (8 . "MASONRY") (62 . 7) (370 . 13) (100 . "AcDbLine") (10 9709.6521719457
4096.9082239819 0.0) (11 9600.3025791855 4096.9082239819 0.0))
((0 . "LINE") (100 . "AcDbEntity") (8 . "MASONRY") (62 . 7) (370 . 13) (100 . "AcDbLine") (10 9739.8190045249
3863.1221719457 0.0) (11 9604.07239819 3863.1221719457 0.0))
((0 . "LINE") (100 . "AcDbEntity") (8 . "MASONRY") (62 . 7) (370 . 13) (100 . "AcDbLine") (10 9604.07239819
3346.5313800905 0.0) (11 9683.257918552 3346.5313800905 0.0))
((0 . "LINE") (100 . "AcDbEntity") (8 . "MASONRY") (62 . 7) (370 . 13) (100 . "AcDbLine") (10 9606.0346380091
3291.8552036199 0.0) (11 9606.0346380091 3283.0341063348 0.0))
((0 . "LINE") (100 . "AcDbEntity") (8 . "MASONRY") (62 . 7) (370 . 13) (100 . "AcDbLine") (10 9606.0346380091
3283.0341063348 0.0) (11 9630.4666515837 3283.0341063348 0.0))
((0 . "LINE") (100 . "AcDbEntity") (8 . "MASONRY") (62 . 7) (370 . 13) (100 . "AcDbLine") (10 9604.07239819
3035.4447171946 0.0) (11 9786.9527828054 3035.4447171946 0.0))
((0 . "LINE") (100 . "AcDbEntity") (8 . "MASONRY") (62 . 7) (370 . 13) (100 . "AcDbLine") (10 9632.276300905
2631.9760972851 0.0) (11 9632.276300905 2603.7017647059 0.0))
((0 . "LINE") (100 . "AcDbEntity") (8 . "MASONRY") (62 . 7) (370 . 13) (100 . "AcDbLine") (10 9632.276300905
2603.7017647059 0.0) (11 9604.07239819 2603.7017647059 0.0))
((0 . "LINE") (100 . "AcDbEntity") (8 . "MASONRY") (62 . 7) (370 . 13) (100 . "AcDbLine") (10 9641.7788687783
2109.7285067873 0.0) (11 9604.07239819 2109.7285067873 0.0))
((0 . "LINE") (100 . "AcDbEntity") (8 . "MASONRY") (62 . 7) (370 . 13) (100 . "AcDbLine") (10 9785.0678733032
1738.3116289593 0.0) (11 9604.07239819 1738.3116289593 0.0))
((0 . "LINE") (100 . "AcDbEntity") (8 . "MASONRY") (62 . 7) (370 . 13) (100 . "AcDbLine") (10 9604.07239819
1527.149321267 0.0) (11 9777.5254751131 1527.149321267 0.0))
((0 . "LINE") (100 . "AcDbEntity") (8 . "MASONRY") (62 . 7) (370 . 13) (100 . "AcDbLine") (10 9604.07239819
1436.6515837104 0.0) (11 9981.1453846154 1436.6515837104 0.0))
((0 . "LINE") (100 . "AcDbEntity") (8 . "MASONRY") (62 . 7) (370 . 13) (100 . "AcDbLine") (10 9604.07239819
1089.7426696833 0.0) (11 9658.7471945701 1089.7426696833 0.0))
((0 . "LINE") (100 . "AcDbEntity") (8 . "MASONRY") (62 . 7) (370 . 13) (100 . "AcDbLine") (10 9615.3846153846
4785.0678733032 0.0) (11 9615.3846153846 4837.857760181 0.0))
((0 . "LINE") (100 . "AcDbEntity") (8 . "MASONRY") (62 . 7) (370 . 13) (100 . "AcDbLine") (10 9615.3846153846
4775.6412556561 0.0) (11 9615.3846153846 4724.7355882353 0.0))
((0 . "LINE") (100 . "AcDbEntity") (8 . "MASONRY") (62 . 7) (370 . 13) (100 . "AcDbLine") (10 9615.3846153846
4785.0678733032 0.0) (11 9615.3846153846 4775.6412556561 0.0))
((0 . "LINE") (100 . "AcDbEntity") (8 . "MASONRY") (62 . 7) (370 . 13) (100 . "AcDbLine") (10 9613.5031561086
4291.1015158371 0.0) (11 9613.5031561086 4272.3242307692 0.0))
((0 . "LINE") (100 . "AcDbEntity") (8 . "MASONRY") (62 . 7) (370 . 13) (100 . "AcDbLine") (10 9613.5031561086
4272.3242307692 0.0) (11 9819.0045248869 4272.3242307692 0.0))
((0 . "LINE") (100 . "AcDbEntity") (8 . "MASONRY") (62 . 7) (370 . 13) (100 . "AcDbLine") (10 9615.3846153846
2631.9760972851 0.0) (11 9632.276300905 2631.9760972851 0.0))
((0 . "LINE") (100 . "AcDbEntity") (8 . "MASONRY") (62 . 7) (370 . 13) (100 . "AcDbLine") (10 9619.1544343891
5840.8749321267 0.0) (11 9634.2392307692 5840.8749321267 0.0))
((0 . "LINE") (100 . "AcDbEntity") (8 . "MASONRY") (62 . 7) (370 . 13) (100 . "AcDbLine") (10 9615.3846153846
4785.0678733032 0.0) (11 9871.7957918552 4785.0678733032 0.0))
((0 . "LINE") (100 . "AcDbEntity") (8 . "MASONRY") (62 . 7) (370 . 13) (100 . "AcDbLine") (10 9871.7957918552
4785.0678733032 0.0) (11 9949.0950226244 4785.0678733032 0.0))
((0 . "LINE") (100 . "AcDbEntity") (8 . "MASONRY") (62 . 7) (370 . 13) (100 . "AcDbLine") (10 9615.3846153846
4724.7355882353 0.0) (11 9671.9457013575 4724.7355882353 0.0))
((0 . "LINE") (100 . "AcDbEntity") (8 . "MASONRY") (62 . 7) (370 . 13) (100 . "AcDbLine") (10 9622.9270135747
5712.6696832579 0.0) (11 9622.9270135747 5678.7330316742 0.0))
((0 . "LINE") (100 . "AcDbEntity") (8 . "MASONRY") (62 . 7) (370 . 13) (100 . "AcDbLine") (10 9634.2392307692
5712.6696832579 0.0) (11 9622.9270135747 5712.6696832579 0.0))
((0 . "LINE") (100 . "AcDbEntity") (8 . "MASONRY") (62 . 7) (370 . 13) (100 . "AcDbLine") (10 9961.0093099548
5678.7330316742 0.0) (11 9622.9270135747 5678.7330316742 0.0))
((0 . "LINE") (100 . "AcDbEntity") (8 . "MASONRY") (62 . 7) (370 . 13) (100 . "AcDbLine") (10 9622.9270135747
2564.1027941176 0.0) (11 9622.9270135747 2518.8539253394 0.0))
((0 . "LINE") (100 . "AcDbEntity") (8 . "MASONRY") (62 . 7) (370 . 13) (100 . "AcDbLine") (10 9653.0910859729
2518.8539253394 0.0) (11 9622.9270135747 2518.8539253394 0.0))
((0 . "LINE") (100 . "AcDbEntity") (8 . "MASONRY") (62 . 7) (370 . 13) (100 . "AcDbLine") (10 9626.6968325792
5791.8552036199 0.0) (11 9638.0090497738 5791.8552036199 0.0))
((0 . "LINE") (100 . "AcDbEntity") (8 . "MASONRY") (62 . 7) (370 . 13) (100 . "AcDbLine") (10 9626.6968325792
5607.0885294118 0.0) (11 9626.6968325792 5641.025520362 0.0))
((0 . "LINE") (100 . "AcDbEntity") (8 . "MASONRY") (62 . 7) (370 . 13) (100 . "AcDbLine") (10 9660.6334841629
5554.9007126697 0.0) (11 9628.6590723982 5554.9007126697 0.0))
((0 . "LINE") (100 . "AcDbEntity") (8 . "MASONRY") (62 . 7) (370 . 13) (100 . "AcDbLine") (10 9628.6590723982
5554.9007126697 0.0) (11 9628.6590723982 5569.3820588235 0.0))
((0 . "LINE") (100 . "AcDbEntity") (8 . "MASONRY") (62 . 7) (370 . 13) (100 . "AcDbLine") (10 9626.6968325792
1176.4705882353 0.0) (11 9626.6968325792 1142.5339366516 0.0))
((0 . "LINE") (100 . "AcDbEntity") (8 . "MASONRY") (62 . 7) (370 . 13) (100 . "AcDbLine") (10 9626.6968325792
1176.4705882353 0.0) (11 9920.814479638 1176.4705882353 0.0))
((0 . "LINE") (100 . "AcDbEntity") (8 . "MASONRY") (62 . 7) (370 . 13) (100 . "AcDbLine") (10 9638.0090497738
6340.4977375566 0.0) (11 9630.4666515837 6340.4977375566 0.0))
((0 . "LINE") (100 . "AcDbEntity") (8 . "MASONRY") (62 . 7) (370 . 13) (100 . "AcDbLine") (10 9630.4666515837
3684.0116063348 0.0) (11 9630.4666515837 3627.450520362 0.0))
((0 . "LINE") (100 . "AcDbEntity") (8 . "MASONRY") (62 . 7) (370 . 13) (100 . "AcDbLine") (10 9732.2766063348
3684.0116063348 0.0) (11 9630.4666515837 3684.0116063348 0.0))
((0 . "LINE") (100 . "AcDbEntity") (8 . "MASONRY") (62 . 7) (370 . 13) (100 . "AcDbLine") (10 9630.4666515837
3597.2850678733 0.0) (11 9754.901040724 3597.2850678733 0.0))
((0 . "LINE") (100 . "AcDbEntity") (8 . "MASONRY") (62 . 7) (370 . 13) (100 . "AcDbLine") (10 9630.4666515837
3597.2850678733 0.0) (11 9630.4666515837 3555.8067081448 0.0))
((0 . "LINE") (100 . "AcDbEntity") (8 . "MASONRY") (62 . 7) (370 . 13) (100 . "AcDbLine") (10 9702.1125339367
3555.8067081448 0.0) (11 9630.4666515837 3555.8067081448 0.0))
((0 . "LINE") (100 . "AcDbEntity") (8 . "MASONRY") (62 . 7) (370 . 13) (100 . "AcDbLine") (10 9630.4666515837
1672.3232352941 0.0) (11 9641.7788687783 1672.3232352941 0.0))
((0 . "LINE") (100 . "AcDbEntity") (8 . "MASONRY") (62 . 7) (370 . 13) (100 . "AcDbLine") (10 9634.2392307692
5519.0784615385 0.0) (11 9794.2362669683 5519.0784615385 0.0))
((0 . "LINE") (100 . "AcDbEntity") (8 . "MASONRY") (62 . 7) (370 . 13) (100 . "AcDbLine") (10 9794.2362669683
5519.0784615385 0.0) (11 9794.2362669683 5558.069841629 0.0))
((0 . "LINE") (100 . "AcDbEntity") (8 . "MASONRY") (62 . 7) (370 . 13) (100 . "AcDbLine") (10 9639.8953393665
3989.4414705882 0.0) (11 9639.8953393665 3955.5048190045 0.0))
((0 . "LINE") (100 . "AcDbEntity") (8 . "MASONRY") (62 . 7) (370 . 13) (100 . "AcDbLine") (10 9845.3987782805
2631.9760972851 0.0) (11 9632.276300905 2631.9760972851 0.0))
((0 . "LINE") (100 . "AcDbEntity") (8 . "MASONRY") (62 . 7) (370 . 13) (100 . "AcDbLine") (10 9638.0090497738
6255.6561085973 0.0) (11 9773.7556561086 6255.6561085973 0.0))
((0 . "LINE") (100 . "AcDbEntity") (8 . "MASONRY") (62 . 7) (370 . 13) (100 . "AcDbLine") (10 9639.893959276
6202.8658823529 0.0) (11 9736.0491855204 6202.8658823529 0.0))
((0 . "LINE") (100 . "AcDbEntity") (8 . "MASONRY") (62 . 7) (370 . 13) (100 . "AcDbLine") (10 9639.893959276
6221.7194570136 0.0) (11 9639.893959276 6202.8658823529 0.0))
((0 . "LINE") (100 . "AcDbEntity") (8 . "MASONRY") (62 . 7) (370 . 13) (100 . "AcDbLine") (10 9732.2779864253
6063.3484162896 0.0) (11 9639.2918891403 6063.3484162896 0.0))
((0 . "LINE") (100 . "AcDbEntity") (8 . "MASONRY") (62 . 7) (370 . 13) (100 . "AcDbLine") (10 9638.0090497738
5742.8354751131 0.0) (11 9638.0090497738 5791.8552036199 0.0))
((0 . "LINE") (100 . "AcDbEntity") (8 . "MASONRY") (62 . 7) (370 . 13) (100 . "AcDbLine") (10 9782.6547737557
5791.8552036199 0.0) (11 9638.0090497738 5791.8552036199 0.0))
((0 . "LINE") (100 . "AcDbEntity") (8 . "MASONRY") (62 . 7) (370 . 13) (100 . "AcDbLine") (10 9638.0090497738
5135.5919457014 0.0) (11 9638.0090497738 5109.3509728507 0.0))
((0 . "LINE") (100 . "AcDbEntity") (8 . "MASONRY") (62 . 7) (370 . 13) (100 . "AcDbLine") (10 9638.0090497738
5135.5919457014 0.0) (11 9785.0678733032 5135.5919457014 0.0))
((0 . "LINE") (100 . "AcDbEntity") (8 . "MASONRY") (62 . 7) (370 . 13) (100 . "AcDbLine") (10 9785.0678733032
5109.3509728507 0.0) (11 9638.0090497738 5109.3509728507 0.0))
((0 . "LINE") (100 . "AcDbEntity") (8 . "MASONRY") (62 . 7) (370 . 13) (100 . "AcDbLine") (10 9638.0090497738
218.7019457014 0.0) (11 9638.0090497738 177.2256561086 0.0))
((0 . "LINE") (100 . "AcDbEntity") (8 . "MASONRY") (62 . 7) (370 . 13) (100 . "AcDbLine") (10 9638.0090497738
177.2256561086 0.0) (11 9809.5772171946 177.2256561086 0.0))
((0 . "LINE") (100 . "AcDbEntity") (8 . "MASONRY") (62 . 7) (370 . 13) (100 . "AcDbLine") (10 9773.7556561086
6297.2887782805 0.0) (11 9643.667918552 6297.2887782805 0.0))
((0 . "LINE") (100 . "AcDbEntity") (8 . "MASONRY") (62 . 7) (370 . 13) (100 . "AcDbLine") (10 9643.667918552
6297.2887782805 0.0) (11 9643.667918552 6312.2171945701 0.0))
((0 . "LINE") (100 . "AcDbEntity") (8 . "MASONRY") (62 . 7) (370 . 13) (100 . "AcDbLine") (10 9641.7788687783
2458.5216402715 0.0) (11 9653.0910859729 2458.5216402715 0.0))
((0 . "LINE") (100 . "AcDbEntity") (8 . "MASONRY") (62 . 7) (370 . 13) (100 . "AcDbLine") (10 9641.7788687783
309.1996832579 0.0) (11 9649.3212669683 309.1996832579 0.0))
((0 . "LINE") (100 . "AcDbEntity") (8 . "MASONRY") (62 . 7) (370 . 13) (100 . "AcDbLine") (10 9649.3212669683
248.8687782805 0.0) (11 9649.3212669683 260.1809954751 0.0))
((0 . "LINE") (100 . "AcDbEntity") (8 . "MASONRY") (62 . 7) (370 . 13) (100 . "AcDbLine") (10 9798.2615497738
4892.5339366516 0.0) (11 9798.2615497738 4937.7058257919 0.0))
((0 . "LINE") (100 . "AcDbEntity") (8 . "MASONRY") (62 . 7) (370 . 13) (100 . "AcDbLine") (10 9798.2615497738
4937.7058257919 0.0) (11 9645.5514479638 4937.7058257919 0.0))
((0 . "LINE") (100 . "AcDbEntity") (8 . "MASONRY") (62 . 7) (370 . 13) (100 . "AcDbLine") (10 9639.8953393665
3989.4414705882 0.0) (11 9656.8636651584 3989.4414705882 0.0))
((0 . "LINE") (100 . "AcDbEntity") (8 . "MASONRY") (62 . 7) (370 . 13) (100 . "AcDbLine") (10 9645.5514479638
3286.1990950226 0.0) (11 9830.3167420814 3286.1990950226 0.0))
((0 . "LINE") (100 . "AcDbEntity") (8 . "MASONRY") (62 . 7) (370 . 13) (100 . "AcDbLine") (10 9647.4363574661
663.6509954751 0.0) (11 9647.4363574661 720.212081448 0.0))
((0 . "LINE") (100 . "AcDbEntity") (8 . "MASONRY") (62 . 7) (370 . 13) (100 . "AcDbLine") (10 10388.3852036199
720.212081448 0.0) (11 9647.4363574661 720.212081448 0.0))
((0 . "LINE") (100 . "AcDbEntity") (8 . "MASONRY") (62 . 7) (370 . 13) (100 . "AcDbLine") (10 9739.8190045249
3917.720678733 0.0) (11 9649.3212669683 3917.720678733 0.0))
((0 . "LINE") (100 . "AcDbEntity") (8 . "MASONRY") (62 . 7) (370 . 13) (100 . "AcDbLine") (10 9649.3212669683
580.6928959276 0.0) (11 9649.3212669683 629.7143438914 0.0))
((0 . "LINE") (100 . "AcDbEntity") (8 . "MASONRY") (62 . 7) (370 . 13) (100 . "AcDbLine") (10 9649.3212669683
271.4932126697 0.0) (11 9649.3212669683 260.1809954751 0.0))
((0 . "LINE") (100 . "AcDbEntity") (8 . "MASONRY") (62 . 7) (370 . 13) (100 . "AcDbLine") (10 9724.7369683258
260.1809954751 0.0) (11 9649.3212669683 260.1809954751 0.0))
((0 . "LINE") (100 . "AcDbEntity") (8 . "MASONRY") (62 . 7) (370 . 13) (100 . "AcDbLine") (10 9679.4880995475
6112.3681447964 0.0) (11 9653.0910859729 6112.3681447964 0.0))
((0 . "LINE") (100 . "AcDbEntity") (8 . "MASONRY") (62 . 7) (370 . 13) (100 . "AcDbLine") (10 9653.0910859729
4977.3755656109 0.0) (11 9653.0910859729 5003.771199095 0.0))
((0 . "LINE") (100 . "AcDbEntity") (8 . "MASONRY") (62 . 7) (370 . 13) (100 . "AcDbLine") (10 9653.0910859729
5003.771199095 0.0) (11 9785.2156334842 5003.771199095 0.0))
((0 . "LINE") (100 . "AcDbEntity") (8 . "MASONRY") (62 . 7) (370 . 13) (100 . "AcDbLine") (10 9785.2156334842
5003.771199095 0.0) (11 9785.2156334842 5064.1021040724 0.0))
((0 . "LINE") (100 . "AcDbEntity") (8 . "MASONRY") (62 . 7) (370 . 13) (100 . "AcDbLine") (10 9653.0910859729
2518.8539253394 0.0) (11 9653.0910859729 2458.5216402715 0.0))
((0 . "LINE") (100 . "AcDbEntity") (8 . "MASONRY") (62 . 7) (370 . 13) (100 . "AcDbLine") (10 10033.9366515837
2518.8539253394 0.0) (11 9653.0910859729 2518.8539253394 0.0))
((0 . "LINE") (100 . "AcDbEntity") (8 . "MASONRY") (62 . 7) (370 . 13) (100 . "AcDbLine") (10 9879.3354298643
2458.5216402715 0.0) (11 9653.0910859729 2458.5216402715 0.0))
((0 . "LINE") (100 . "AcDbEntity") (8 . "MASONRY") (62 . 7) (370 . 13) (100 . "AcDbLine") (10 9653.0910859729
1858.9741289593 0.0) (11 9653.0910859729 1885.3697624434 0.0))
((0 . "LINE") (100 . "AcDbEntity") (8 . "MASONRY") (62 . 7) (370 . 13) (100 . "AcDbLine") (10 9653.0910859729
1858.9741289593 0.0) (11 9736.0491855204 1858.9741289593 0.0))
((0 . "LINE") (100 . "AcDbEntity") (8 . "MASONRY") (62 . 7) (370 . 13) (100 . "AcDbLine") (10 9658.7471945701
1040.7239819005 0.0) (11 9658.7471945701 1089.7426696833 0.0))
((0 . "LINE") (100 . "AcDbEntity") (8 . "MASONRY") (62 . 7) (370 . 13) (100 . "AcDbLine") (10 9664.4033031674
1938.1596493213 0.0) (11 9664.4033031674 1945.7013574661 0.0))
((0 . "LINE") (100 . "AcDbEntity") (8 . "MASONRY") (62 . 7) (370 . 13) (100 . "AcDbLine") (10 9700.3028846154
1240.5740723982 0.0) (11 9664.4033031674 1240.5740723982 0.0))
((0 . "LINE") (100 . "AcDbEntity") (8 . "MASONRY") (62 . 7) (370 . 13) (100 . "AcDbLine") (10 9658.7471945701
1089.7426696833 0.0) (11 9683.257918552 1089.7426696833 0.0))
((0 . "LINE") (100 . "AcDbEntity") (8 . "MASONRY") (62 . 7) (370 . 13) (100 . "AcDbLine") (10 9668.1758823529
4626.6968325792 0.0) (11 9683.257918552 4626.6968325792 0.0))
((0 . "LINE") (100 . "AcDbEntity") (8 . "MASONRY") (62 . 7) (370 . 13) (100 . "AcDbLine") (10 9702.1125339367
2109.7285067873 0.0) (11 9668.1758823529 2109.7285067873 0.0))
((0 . "LINE") (100 . "AcDbEntity") (8 . "MASONRY") (62 . 7) (370 . 13) (100 . "AcDbLine") (10 9671.9457013575
4709.6535520362 0.0) (11 9671.9457013575 4724.7355882353 0.0))
((0 . "LINE") (100 . "AcDbEntity") (8 . "MASONRY") (62 . 7) (370 . 13) (100 . "AcDbLine") (10 9671.9457013575
4724.7355882353 0.0) (11 9950.9813122172 4724.7355882353 0.0))
((0 . "LINE") (100 . "AcDbEntity") (8 . "MASONRY") (62 . 7) (370 . 13) (100 . "AcDbLine") (10 9673.8306108597
4690.7989366516 0.0) (11 9673.8306108597 4668.1745022624 0.0))
((0 . "LINE") (100 . "AcDbEntity") (8 . "MASONRY") (62 . 7) (370 . 13) (100 . "AcDbLine") (10 9671.9457013575
991.7052941176 0.0) (11 9671.9457013575 961.5384615385 0.0))
((0 . "LINE") (100 . "AcDbEntity") (8 . "MASONRY") (62 . 7) (370 . 13) (100 . "AcDbLine") (10 9671.9457013575
991.7052941176 0.0) (11 9800.1512895928 991.7052941176 0.0))
((0 . "LINE") (100 . "AcDbEntity") (8 . "MASONRY") (62 . 7) (370 . 13) (100 . "AcDbLine") (10 9675.715520362
5556.1842420814 0.0) (11 9739.8190045249 5556.1842420814 0.0))
((0 . "LINE") (100 . "AcDbEntity") (8 . "MASONRY") (62 . 7) (370 . 13) (100 . "AcDbLine") (10 9675.715520362
3989.4414705882 0.0) (11 9888.7627375566 3989.4414705882 0.0))
((0 . "LINE") (100 . "AcDbEntity") (8 . "MASONRY") (62 . 7) (370 . 13) (100 . "AcDbLine") (10 9675.715520362
2601.8099547511 0.0) (11 9717.1945701357 2601.8099547511 0.0))
((0 . "LINE") (100 . "AcDbEntity") (8 . "MASONRY") (62 . 7) (370 . 13) (100 . "AcDbLine") (10 9675.715520362
1676.0930542986 0.0) (11 9743.5888235294 1676.0930542986 0.0))
((0 . "LINE") (100 . "AcDbEntity") (8 . "MASONRY") (62 . 7) (370 . 13) (100 . "AcDbLine") (10 9679.4880995475
5833.3332126697 0.0) (11 9782.6547737557 5833.3332126697 0.0))
((0 . "LINE") (100 . "AcDbEntity") (8 . "MASONRY") (62 . 7) (370 . 13) (100 . "AcDbLine") (10 9679.4880995475
916.2122624434 0.0) (11 9794.493800905 916.2122624434 0.0))
((0 . "LINE") (100 . "AcDbEntity") (8 . "MASONRY") (62 . 7) (370 . 13) (100 . "AcDbLine") (10 9794.493800905
916.2122624434 0.0) (11 9794.493800905 901.2075565611 0.0))
((0 . "LINE") (100 . "AcDbEntity") (8 . "MASONRY") (62 . 7) (370 . 13) (100 . "AcDbLine") (10 9687.0291176471
2237.9340950226 0.0) (11 9811.4621266968 2237.9340950226 0.0))
((0 . "LINE") (100 . "AcDbEntity") (8 . "MASONRY") (62 . 7) (370 . 13) (100 . "AcDbLine") (10 9687.0291176471
2237.9340950226 0.0) (11 9687.0291176471 2266.2139479638 0.0))
((0 . "LINE") (100 . "AcDbEntity") (8 . "MASONRY") (62 . 7) (370 . 13) (100 . "AcDbLine") (10 9687.0277375566
1936.2740497738 0.0) (11 9698.3399547511 1936.2740497738 0.0))
((0 . "LINE") (100 . "AcDbEntity") (8 . "MASONRY") (62 . 7) (370 . 13) (100 . "AcDbLine") (10 9690.8003167421
6106.7120361991 0.0) (11 9717.1945701357 6106.7120361991 0.0))
((0 . "LINE") (100 . "AcDbEntity") (8 . "MASONRY") (62 . 7) (370 . 13) (100 . "AcDbLine") (10 9717.1945701357
6106.7120361991 0.0) (11 9732.2779864253 6106.7120361991 0.0))
((0 . "LINE") (100 . "AcDbEntity") (8 . "MASONRY") (62 . 7) (370 . 13) (100 . "AcDbLine") (10 9694.5701357466
5439.2908710407 0.0) (11 9788.8363122172 5439.2908710407 0.0))
((0 . "LINE") (100 . "AcDbEntity") (8 . "MASONRY") (62 . 7) (370 . 13) (100 . "AcDbLine") (10 9854.8274660633
4611.6134162896 0.0) (11 9854.8274660633 4624.7339027149 0.0))
((0 . "LINE") (100 . "AcDbEntity") (8 . "MASONRY") (62 . 7) (370 . 13) (100 . "AcDbLine") (10 9854.8274660633
4624.7339027149 0.0) (11 9698.3399547511 4624.7339027149 0.0))
((0 . "LINE") (100 . "AcDbEntity") (8 . "MASONRY") (62 . 7) (370 . 13) (100 . "AcDbLine") (10 9700.3028846154
1240.5740723982 0.0) (11 9715.3096606335 1240.5740723982 0.0))
((0 . "LINE") (100 . "AcDbEntity") (8 . "MASONRY") (62 . 7) (370 . 13) (100 . "AcDbLine") (10 9700.3028846154
1240.5740723982 0.0) (11 9700.3028846154 1258.2155769231 0.0))
((0 . "LINE") (100 . "AcDbEntity") (8 . "MASONRY") (62 . 7) (370 . 13) (100 . "AcDbLine") (10 9700.3028846154
1258.2155769231 0.0) (11 9715.3096606335 1258.2155769231 0.0))
((0 . "LINE") (100 . "AcDbEntity") (8 . "MASONRY") (62 . 7) (370 . 13) (100 . "AcDbLine") (10 9705.8823529412
5346.9075339367 0.0) (11 9705.8823529412 5335.5953167421 0.0))
((0 . "LINE") (100 . "AcDbEntity") (8 . "MASONRY") (62 . 7) (370 . 13) (100 . "AcDbLine") (10 9788.8363122172
5439.2908710407 0.0) (11 9788.8363122172 5392.7591628959 0.0))
((0 . "LINE") (100 . "AcDbEntity") (8 . "MASONRY") (62 . 7) (370 . 13) (100 . "AcDbLine") (10 9788.8363122172
5392.7591628959 0.0) (11 9709.6521719457 5392.7591628959 0.0))
((0 . "LINE") (100 . "AcDbEntity") (8 . "MASONRY") (62 . 7) (370 . 13) (100 . "AcDbLine") (10 9883.1080090498
2833.7104072398 0.0) (11 9709.6521719457 2833.7104072398 0.0))
((0 . "LINE") (100 . "AcDbEntity") (8 . "MASONRY") (62 . 7) (370 . 13) (100 . "AcDbLine") (10 9715.3096606335
2771.4932126697 0.0) (11 9837.8591402715 2771.4932126697 0.0))
((0 . "LINE") (100 . "AcDbEntity") (8 . "MASONRY") (62 . 7) (370 . 13) (100 . "AcDbLine") (10 9715.3096606335
2771.4932126697 0.0) (11 9715.3096606335 2801.6593552036 0.0))
((0 . "LINE") (100 . "AcDbEntity") (8 . "MASONRY") (62 . 7) (370 . 13) (100 . "AcDbLine") (10 9732.2766063348
1240.5740723982 0.0) (11 9715.3096606335 1240.5740723982 0.0))
((0 . "LINE") (100 . "AcDbEntity") (8 . "MASONRY") (62 . 7) (370 . 13) (100 . "AcDbLine") (10 9715.3096606335
1258.2155769231 0.0) (11 9715.3096606335 1240.5740723982 0.0))
((0 . "LINE") (100 . "AcDbEntity") (8 . "MASONRY") (62 . 7) (370 . 13) (100 . "AcDbLine") (10 9719.079479638
5976.6215384615 0.0) (11 9719.079479638 5953.9971040724 0.0))
((0 . "LINE") (100 . "AcDbEntity") (8 . "MASONRY") (62 . 7) (370 . 13) (100 . "AcDbLine") (10 9717.1945701357
2911.0103280543 0.0) (11 9717.1945701357 2880.8448755656 0.0))
((0 . "LINE") (100 . "AcDbEntity") (8 . "MASONRY") (62 . 7) (370 . 13) (100 . "AcDbLine") (10 9728.5067873303
1613.877239819 0.0) (11 9719.079479638 1613.877239819 0.0))
((0 . "LINE") (100 . "AcDbEntity") (8 . "MASONRY") (62 . 7) (370 . 13) (100 . "AcDbLine") (10 9719.079479638
1628.9592760181 0.0) (11 9719.079479638 1613.877239819 0.0))
((0 . "LINE") (100 . "AcDbEntity") (8 . "MASONRY") (62 . 7) (370 . 13) (100 . "AcDbLine") (10 9732.2766063348
1258.2155769231 0.0) (11 9715.3096606335 1258.2155769231 0.0))
((0 . "LINE") (100 . "AcDbEntity") (8 . "MASONRY") (62 . 7) (370 . 13) (100 . "AcDbLine") (10 10039.592760181
5953.9971040724 0.0) (11 9719.079479638 5953.9971040724 0.0))
((0 . "LINE") (100 . "AcDbEntity") (8 . "MASONRY") (62 . 7) (370 . 13) (100 . "AcDbLine") (10 9720.9643891403
852.1874886878 0.0) (11 9751.1312217195 852.1874886878 0.0))
((0 . "LINE") (100 . "AcDbEntity") (8 . "MASONRY") (62 . 7) (370 . 13) (100 . "AcDbLine") (10 9743.4051696833
3352.1867986425 0.0) (11 9743.4051696833 3337.7061425339 0.0))
((0 . "LINE") (100 . "AcDbEntity") (8 . "MASONRY") (62 . 7) (370 . 13) (100 . "AcDbLine") (10 9743.4051696833
3337.7061425339 0.0) (11 9724.7369683258 3337.7061425339 0.0))
((0 . "LINE") (100 . "AcDbEntity") (8 . "MASONRY") (62 . 7) (370 . 13) (100 . "AcDbLine") (10 9852.9411764706
6063.3484162896 0.0) (11 9732.2779864253 6063.3484162896 0.0))
((0 . "LINE") (100 . "AcDbEntity") (8 . "MASONRY") (62 . 7) (370 . 13) (100 . "AcDbLine") (10 9732.2779864253
6106.7120361991 0.0) (11 9732.2779864253 6063.3484162896 0.0))
((0 . "LINE") (100 . "AcDbEntity") (8 . "MASONRY") (62 . 7) (370 . 13) (100 . "AcDbLine") (10 9796.3800904977
2269.9851470588 0.0) (11 9728.5067873303 2269.9851470588 0.0))
((0 . "LINE") (100 . "AcDbEntity") (8 . "MASONRY") (62 . 7) (370 . 13) (100 . "AcDbLine") (10 9728.5067873303
1340.4977375566 0.0) (11 9769.9858371041 1340.4977375566 0.0))
((0 . "LINE") (100 . "AcDbEntity") (8 . "MASONRY") (62 . 7) (370 . 13) (100 . "AcDbLine") (10 9971.7194570136
6014.3286877828 0.0) (11 9732.2766063348 6014.3286877828 0.0))
((0 . "LINE") (100 . "AcDbEntity") (8 . "MASONRY") (62 . 7) (370 . 13) (100 . "AcDbLine") (10 9732.2766063348
4470.2113914027 0.0) (11 9747.3614027149 4470.2113914027 0.0))
((0 . "LINE") (100 . "AcDbEntity") (8 . "MASONRY") (62 . 7) (370 . 13) (100 . "AcDbLine") (10 9743.5888235294
6106.7120361991 0.0) (11 9732.2779864253 6106.7120361991 0.0))
((0 . "LINE") (100 . "AcDbEntity") (8 . "MASONRY") (62 . 7) (370 . 13) (100 . "AcDbLine") (10 9736.0491855204
4068.6269909502 0.0) (11 9754.901040724 4068.6269909502 0.0))
((0 . "LINE") (100 . "AcDbEntity") (8 . "MASONRY") (62 . 7) (370 . 13) (100 . "AcDbLine") (10 9739.8190045249
3863.1221719457 0.0) (11 9739.8190045249 3917.720678733 0.0))
((0 . "LINE") (100 . "AcDbEntity") (8 . "MASONRY") (62 . 7) (370 . 13) (100 . "AcDbLine") (10 9890.6476470588
3917.720678733 0.0) (11 9754.901040724 3917.720678733 0.0))
((0 . "LINE") (100 . "AcDbEntity") (8 . "MASONRY") (62 . 7) (370 . 13) (100 . "AcDbLine") (10 9754.901040724
3917.720678733 0.0) (11 9739.8190045249 3917.720678733 0.0))
((0 . "LINE") (100 . "AcDbEntity") (8 . "MASONRY") (62 . 7) (370 . 13) (100 . "AcDbLine") (10 9888.7627375566
3863.1221719457 0.0) (11 9739.8190045249 3863.1221719457 0.0))
((0 . "LINE") (100 . "AcDbEntity") (8 . "MASONRY") (62 . 7) (370 . 13) (100 . "AcDbLine") (10 9743.5888235294
1700.60239819 0.0) (11 9743.5888235294 1676.0930542986 0.0))
((0 . "LINE") (100 . "AcDbEntity") (8 . "MASONRY") (62 . 7) (370 . 13) (100 . "AcDbLine") (10 10128.2042081448
1676.0930542986 0.0) (11 9743.5888235294 1676.0930542986 0.0))
((0 . "LINE") (100 . "AcDbEntity") (8 . "MASONRY") (62 . 7) (370 . 13) (100 . "AcDbLine") (10 9754.901040724
1380.0904977376 0.0) (11 9743.5888235294 1380.0904977376 0.0))
((0 . "LINE") (100 . "AcDbEntity") (8 . "MASONRY") (62 . 7) (370 . 13) (100 . "AcDbLine") (10 9860.4835746606
2110.4099773756 0.0) (11 9747.3614027149 2110.4099773756 0.0))
((0 . "LINE") (100 . "AcDbEntity") (8 . "MASONRY") (62 . 7) (370 . 13) (100 . "AcDbLine") (10 9754.901040724
3559.5779072398 0.0) (11 9754.901040724 3552.036199095 0.0))
((0 . "LINE") (100 . "AcDbEntity") (8 . "MASONRY") (62 . 7) (370 . 13) (100 . "AcDbLine") (10 9753.0161312217
1934.3891402715 0.0) (11 9753.0161312217 1987.1797171946 0.0))
((0 . "LINE") (100 . "AcDbEntity") (8 . "MASONRY") (62 . 7) (370 . 13) (100 . "AcDbLine") (10 9754.901040724
4098.7938235294 0.0) (11 9754.901040724 4068.6269909502 0.0))
((0 . "LINE") (100 . "AcDbEntity") (8 . "MASONRY") (62 . 7) (370 . 13) (100 . "AcDbLine") (10 9754.901040724
4098.7938235294 0.0) (11 9860.6672285068 4098.7938235294 0.0))
((0 . "LINE") (100 . "AcDbEntity") (8 . "MASONRY") (62 . 7) (370 . 13) (100 . "AcDbLine") (10 9754.901040724
4068.6269909502 0.0) (11 9762.443438914 4068.6269909502 0.0))
((0 . "LINE") (100 . "AcDbEntity") (8 . "MASONRY") (62 . 7) (370 . 13) (100 . "AcDbLine") (10 9754.901040724
3559.5779072398 0.0) (11 9754.901040724 3597.2850678733 0.0))
((0 . "LINE") (100 . "AcDbEntity") (8 . "MASONRY") (62 . 7) (370 . 13) (100 . "AcDbLine") (10 9988.6877828054
3597.2850678733 0.0) (11 9754.901040724 3597.2850678733 0.0))
((0 . "LINE") (100 . "AcDbEntity") (8 . "MASONRY") (62 . 7) (370 . 13) (100 . "AcDbLine") (10 9754.901040724
3559.5779072398 0.0) (11 9852.9411764706 3559.5779072398 0.0))
((0 . "LINE") (100 . "AcDbEntity") (8 . "MASONRY") (62 . 7) (370 . 13) (100 . "AcDbLine") (10 9937.7054751131
1987.1797171946 0.0) (11 9753.0161312217 1987.1797171946 0.0))
((0 . "LINE") (100 . "AcDbEntity") (8 . "MASONRY") (62 . 7) (370 . 13) (100 . "AcDbLine") (10 9877.450520362
6206.6363800905 0.0) (11 9762.443438914 6206.6363800905 0.0))
((0 . "LINE") (100 . "AcDbEntity") (8 . "MASONRY") (62 . 7) (370 . 13) (100 . "AcDbLine") (10 9884.9155882353
5248.8687782805 0.0) (11 9884.9155882353 5316.8967420814 0.0))
((0 . "LINE") (100 . "AcDbEntity") (8 . "MASONRY") (62 . 7) (370 . 13) (100 . "AcDbLine") (10 9884.9155882353
5316.8967420814 0.0) (11 9807.6985180995 5316.8967420814 0.0))
((0 . "LINE") (100 . "AcDbEntity") (8 . "MASONRY") (62 . 7) (370 . 13) (100 . "AcDbLine") (10 9807.6985180995
5316.8967420814 0.0) (11 9766.2132579186 5316.8967420814 0.0))
((0 . "LINE") (100 . "AcDbEntity") (8 . "MASONRY") (62 . 7) (370 . 13) (100 . "AcDbLine") (10 9766.2132579186
2894.0426923077 0.0) (11 9875.5656108597 2894.0426923077 0.0))
((0 . "LINE") (100 . "AcDbEntity") (8 . "MASONRY") (62 . 7) (370 . 13) (100 . "AcDbLine") (10 9781.2966742081
260.1809954751 0.0) (11 9766.2132579186 260.1809954751 0.0))
((0 . "LINE") (100 . "AcDbEntity") (8 . "MASONRY") (62 . 7) (370 . 13) (100 . "AcDbLine") (10 9782.6547737557
5791.8552036199 0.0) (11 9782.6547737557 5765.4599095023 0.0))
((0 . "LINE") (100 . "AcDbEntity") (8 . "MASONRY") (62 . 7) (370 . 13) (100 . "AcDbLine") (10 9782.6547737557
5765.4599095023 0.0) (11 9782.6547737557 5750.3771945701 0.0))
((0 . "LINE") (100 . "AcDbEntity") (8 . "MASONRY") (62 . 7) (370 . 13) (100 . "AcDbLine") (10 9769.9858371041
1608.2211312217 0.0) (11 9826.5469230769 1608.2211312217 0.0))
((0 . "LINE") (100 . "AcDbEntity") (8 . "MASONRY") (62 . 7) (370 . 13) (100 . "AcDbLine") (10 9773.7556561086
6255.6561085973 0.0) (11 9773.7556561086 6297.2887782805 0.0))
((0 . "LINE") (100 . "AcDbEntity") (8 . "MASONRY") (62 . 7) (370 . 13) (100 . "AcDbLine") (10 9966.0633484163
6297.2887782805 0.0) (11 9773.7556561086 6297.2887782805 0.0))
((0 . "LINE") (100 . "AcDbEntity") (8 . "MASONRY") (62 . 7) (370 . 13) (100 . "AcDbLine") (10 9773.7556561086
6255.6561085973 0.0) (11 9943.4389140272 6255.6561085973 0.0))
((0 . "LINE") (100 . "AcDbEntity") (8 . "MASONRY") (62 . 7) (370 . 13) (100 . "AcDbLine") (10 9777.5254751131
3695.3238235294 0.0) (11 9785.0678733032 3695.3238235294 0.0))
((0 . "LINE") (100 . "AcDbEntity") (8 . "MASONRY") (62 . 7) (370 . 13) (100 . "AcDbLine") (10 9785.0678733032
1738.3116289593 0.0) (11 9785.0678733032 1800.4508031674 0.0))
((0 . "LINE") (100 . "AcDbEntity") (8 . "MASONRY") (62 . 7) (370 . 13) (100 . "AcDbLine") (10 9807.6923076923
1234.9165837104 0.0) (11 9777.5254751131 1234.9165837104 0.0))
((0 . "LINE") (100 . "AcDbEntity") (8 . "MASONRY") (62 . 7) (370 . 13) (100 . "AcDbLine") (10 9781.2966742081
260.1809954751 0.0) (11 9939.6690950226 260.1809954751 0.0))
((0 . "LINE") (100 . "AcDbEntity") (8 . "MASONRY") (62 . 7) (370 . 13) (100 . "AcDbLine") (10 9781.2966742081
260.1809954751 0.0) (11 9781.2966742081 354.4485520362 0.0))
((0 . "LINE") (100 . "AcDbEntity") (8 . "MASONRY") (62 . 7) (370 . 13) (100 . "AcDbLine") (10 9781.2980542986
6104.8264253394 0.0) (11 9796.3800904977 6104.8264253394 0.0))
((0 . "LINE") (100 . "AcDbEntity") (8 . "MASONRY") (62 . 7) (370 . 13) (100 . "AcDbLine") (10 9782.6547737557
5791.8552036199 0.0) (11 9782.6547737557 5833.3332126697 0.0))
((0 . "LINE") (100 . "AcDbEntity") (8 . "MASONRY") (62 . 7) (370 . 13) (100 . "AcDbLine") (10 9864.2533936652
5109.3509728507 0.0) (11 9796.386300905 5109.3509728507 0.0))
((0 . "LINE") (100 . "AcDbEntity") (8 . "MASONRY") (62 . 7) (370 . 13) (100 . "AcDbLine") (10 9796.386300905
5109.3509728507 0.0) (11 9785.0678733032 5109.3509728507 0.0))
((0 . "LINE") (100 . "AcDbEntity") (8 . "MASONRY") (62 . 7) (370 . 13) (100 . "AcDbLine") (10 9785.0678733032
5135.5919457014 0.0) (11 9785.0678733032 5109.3509728507 0.0))
((0 . "LINE") (100 . "AcDbEntity") (8 . "MASONRY") (62 . 7) (370 . 13) (100 . "AcDbLine") (10 9913.272081448
1340.4977375566 0.0) (11 9781.2980542986 1340.4977375566 0.0))
((0 . "LINE") (100 . "AcDbEntity") (8 . "MASONRY") (62 . 7) (370 . 13) (100 . "AcDbLine") (10 9782.6547737557
5833.3332126697 0.0) (11 9879.3354298643 5833.3332126697 0.0))
((0 . "LINE") (100 . "AcDbEntity") (8 . "MASONRY") (62 . 7) (370 . 13) (100 . "AcDbLine") (10 9785.0678733032
3695.3238235294 0.0) (11 9785.0678733032 3706.636040724 0.0))
((0 . "LINE") (100 . "AcDbEntity") (8 . "MASONRY") (62 . 7) (370 . 13) (100 . "AcDbLine") (10 9841.628959276
3695.3238235294 0.0) (11 9785.0678733032 3695.3238235294 0.0))
((0 . "LINE") (100 . "AcDbEntity") (8 . "MASONRY") (62 . 7) (370 . 13) (100 . "AcDbLine") (10 9786.9527828054
2948.718178733 0.0) (11 9786.9527828054 3035.4447171946 0.0))
((0 . "LINE") (100 . "AcDbEntity") (8 . "MASONRY") (62 . 7) (370 . 13) (100 . "AcDbLine") (10 9815.2347058824
3035.4447171946 0.0) (11 9786.9527828054 3035.4447171946 0.0))
((0 . "LINE") (100 . "AcDbEntity") (8 . "MASONRY") (62 . 7) (370 . 13) (100 . "AcDbLine") (10 9785.0678733032
1855.2036199095 0.0) (11 9785.0678733032 1800.4508031674 0.0))
((0 . "LINE") (100 . "AcDbEntity") (8 . "MASONRY") (62 . 7) (370 . 13) (100 . "AcDbLine") (10 9785.0678733032
1800.4508031674 0.0) (11 9873.679321267 1800.4508031674 0.0))
((0 . "LINE") (100 . "AcDbEntity") (8 . "MASONRY") (62 . 7) (370 . 13) (100 . "AcDbLine") (10 9873.679321267
1800.4508031674 0.0) (11 9873.679321267 1776.0180995475 0.0))
((0 . "LINE") (100 . "AcDbEntity") (8 . "MASONRY") (62 . 7) (370 . 13) (100 . "AcDbLine") (10 9852.9411764706
354.4485520362 0.0) (11 9781.2966742081 354.4485520362 0.0))
((0 . "LINE") (100 . "AcDbEntity") (8 . "MASONRY") (62 . 7) (370 . 13) (100 . "AcDbLine") (10 9785.0678733032
5135.5919457014 0.0) (11 9969.8331674208 5135.5919457014 0.0))
((0 . "LINE") (100 . "AcDbEntity") (8 . "MASONRY") (62 . 7) (370 . 13) (100 . "AcDbLine") (10 9969.8331674208
5135.5919457014 0.0) (11 10000 5135.5919457014 0.0))
((0 . "LINE") (100 . "AcDbEntity") (8 . "MASONRY") (62 . 7) (370 . 13) (100 . "AcDbLine") (10 10000 5135.5919457014 0.0)
(11 10354.4485520362 5135.5919457014 0.0))
((0 . "LINE") (100 . "AcDbEntity") (8 . "MASONRY") (62 . 7) (370 . 13) (100 . "AcDbLine") (10 9898.1900452489
5439.2908710407 0.0) (11 9788.8363122172 5439.2908710407 0.0))
((0 . "LINE") (100 . "AcDbEntity") (8 . "MASONRY") (62 . 7) (370 . 13) (100 . "AcDbLine") (10 9792.6102714932
2326.5462330317 0.0) (11 9792.6102714932 2345.3994683258 0.0))
((0 . "LINE") (100 . "AcDbEntity") (8 . "MASONRY") (62 . 7) (370 . 13) (100 . "AcDbLine") (10 9867.3693665158
537.3303167421 0.0) (11 9792.6102714932 537.3303167421 0.0))
((0 . "LINE") (100 . "AcDbEntity") (8 . "MASONRY") (62 . 7) (370 . 13) (100 . "AcDbLine") (10 9803.9224886878 4475.8675
0.0) (11 9796.3800904977 4475.8675 0.0))
((0 . "LINE") (100 . "AcDbEntity") (8 . "MASONRY") (62 . 7) (370 . 13) (100 . "AcDbLine") (10 9798.265 4411.7647058824
0.0) (11 9815.2347058824 4411.7647058824 0.0))
((0 . "LINE") (100 . "AcDbEntity") (8 . "MASONRY") (62 . 7) (370 . 13) (100 . "AcDbLine") (10 9798.265 4411.7647058824
0.0) (11 9798.265 4434.3891402715 0.0))
((0 . "LINE") (100 . "AcDbEntity") (8 . "MASONRY") (62 . 7) (370 . 13) (100 . "AcDbLine") (10 9796.3800904977
4068.6269909502 0.0) (11 9811.4621266968 4068.6269909502 0.0))
((0 . "LINE") (100 . "AcDbEntity") (8 . "MASONRY") (62 . 7) (370 . 13) (100 . "AcDbLine") (10 9796.3800904977
2269.9851470588 0.0) (11 9796.3800904977 2303.9217986425 0.0))
((0 . "LINE") (100 . "AcDbEntity") (8 . "MASONRY") (62 . 7) (370 . 13) (100 . "AcDbLine") (10 9811.4621266968
2269.9851470588 0.0) (11 9796.3800904977 2269.9851470588 0.0))
((0 . "LINE") (100 . "AcDbEntity") (8 . "MASONRY") (62 . 7) (370 . 13) (100 . "AcDbLine") (10 9888.7627375566
991.7052941176 0.0) (11 9800.1512895928 991.7052941176 0.0))
((0 . "LINE") (100 . "AcDbEntity") (8 . "MASONRY") (62 . 7) (370 . 13) (100 . "AcDbLine") (10 9800.1512895928
946.4564253394 0.0) (11 9800.1512895928 991.7052941176 0.0))
((0 . "LINE") (100 . "AcDbEntity") (8 . "MASONRY") (62 . 7) (370 . 13) (100 . "AcDbLine") (10 9803.9211085973
4973.6043665158 0.0) (11 9803.9211085973 4992.4589819005 0.0))
((0 . "LINE") (100 . "AcDbEntity") (8 . "MASONRY") (62 . 7) (370 . 13) (100 . "AcDbLine") (10 9798.2615497738
4892.5339366516 0.0) (11 9911.3871719457 4892.5339366516 0.0))
((0 . "LINE") (100 . "AcDbEntity") (8 . "MASONRY") (62 . 7) (370 . 13) (100 . "AcDbLine") (10 9800.1499095023
3394.2672285068 0.0) (11 9800.1499095023 3335.2184728507 0.0))
((0 . "LINE") (100 . "AcDbEntity") (8 . "MASONRY") (62 . 7) (370 . 13) (100 . "AcDbLine") (10 9800.1499095023
3335.2184728507 0.0) (11 9819.0045248869 3335.2184728507 0.0))
((0 . "LINE") (100 . "AcDbEntity") (8 . "MASONRY") (62 . 7) (370 . 13) (100 . "AcDbLine") (10 9800.1499095023
3394.2672285068 0.0) (11 9800.1499095023 3414.4046832579 0.0))
((0 . "LINE") (100 . "AcDbEntity") (8 . "MASONRY") (62 . 7) (370 . 13) (100 . "AcDbLine") (10 9800.1499095023
3394.2672285068 0.0) (11 9822.7722737557 3394.2672285068 0.0))
((0 . "LINE") (100 . "AcDbEntity") (8 . "MASONRY") (62 . 7) (370 . 13) (100 . "AcDbLine") (10 9822.7722737557
3394.2672285068 0.0) (11 9822.7722737557 3414.4046832579 0.0))
((0 . "LINE") (100 . "AcDbEntity") (8 . "MASONRY") (62 . 7) (370 . 13) (100 . "AcDbLine") (10 9890.6476470588
1930.6186312217 0.0) (11 9800.1499095023 1930.6186312217 0.0))
((0 . "LINE") (100 . "AcDbEntity") (8 . "MASONRY") (62 . 7) (370 . 13) (100 . "AcDbLine") (10 9800.1499095023
1040.5755316742 0.0) (11 9822.7743438914 1040.5755316742 0.0))
((0 . "LINE") (100 . "AcDbEntity") (8 . "MASONRY") (62 . 7) (370 . 13) (100 . "AcDbLine") (10 9822.7743438914
1040.5755316742 0.0) (11 9884.9887782805 1040.5755316742 0.0))
((0 . "LINE") (100 . "AcDbEntity") (8 . "MASONRY") (62 . 7) (370 . 13) (100 . "AcDbLine") (10 9884.9887782805
1040.5755316742 0.0) (11 9884.9887782805 1093.5152488688 0.0))
((0 . "LINE") (100 . "AcDbEntity") (8 . "MASONRY") (62 . 7) (370 . 13) (100 . "AcDbLine") (10 9800.1499095023
848.4162895928 0.0) (11 9815.2347058824 848.4162895928 0.0))
((0 . "LINE") (100 . "AcDbEntity") (8 . "MASONRY") (62 . 7) (370 . 13) (100 . "AcDbLine") (10 9800.1499095023
3414.4046832579 0.0) (11 9822.7722737557 3414.4046832579 0.0))
((0 . "LINE") (100 . "AcDbEntity") (8 . "MASONRY") (62 . 7) (370 . 13) (100 . "AcDbLine") (10 9856.7109954751
801.2825113122 0.0) (11 9803.9224886878 801.2825113122 0.0))
((0 . "LINE") (100 . "AcDbEntity") (8 . "MASONRY") (62 . 7) (370 . 13) (100 . "AcDbLine") (10 9807.6923076923
6108.5972850679 0.0) (11 9826.5469230769 6108.5972850679 0.0))
((0 . "LINE") (100 . "AcDbEntity") (8 . "MASONRY") (62 . 7) (370 . 13) (100 . "AcDbLine") (10 9809.5772171946
188.5378733032 0.0) (11 9809.5772171946 177.2256561086 0.0))
((0 . "LINE") (100 . "AcDbEntity") (8 . "MASONRY") (62 . 7) (370 . 13) (100 . "AcDbLine") (10 9809.5772171946
177.2256561086 0.0) (11 9952.8689819005 177.2256561086 0.0))
((0 . "LINE") (100 . "AcDbEntity") (8 . "MASONRY") (62 . 7) (370 . 13) (100 . "AcDbLine") (10 9811.4621266968
2269.9851470588 0.0) (11 9811.4621266968 2237.9340950226 0.0))
((0 . "LINE") (100 . "AcDbEntity") (8 . "MASONRY") (62 . 7) (370 . 13) (100 . "AcDbLine") (10 9901.9598642534
2269.9851470588 0.0) (11 9811.4621266968 2269.9851470588 0.0))
((0 . "LINE") (100 . "AcDbEntity") (8 . "MASONRY") (62 . 7) (370 . 13) (100 . "AcDbLine") (10 9811.4621266968
2237.9340950226 0.0) (11 9826.5469230769 2237.9340950226 0.0))
((0 . "LINE") (100 . "AcDbEntity") (8 . "MASONRY") (62 . 7) (370 . 13) (100 . "AcDbLine") (10 9822.7743438914
1855.2036199095 0.0) (11 9834.086561086 1855.2036199095 0.0))
((0 . "LINE") (100 . "AcDbEntity") (8 . "MASONRY") (62 . 7) (370 . 13) (100 . "AcDbLine") (10 9830.3167420814
1525.2644117647 0.0) (11 9822.7743438914 1525.2644117647 0.0))
((0 . "LINE") (100 . "AcDbEntity") (8 . "MASONRY") (62 . 7) (370 . 13) (100 . "AcDbLine") (10 9822.7743438914
1481.9004524887 0.0) (11 9822.7743438914 1474.3580542986 0.0))
((0 . "LINE") (100 . "AcDbEntity") (8 . "MASONRY") (62 . 7) (370 . 13) (100 . "AcDbLine") (10 9822.7722737557
3414.4046832579 0.0) (11 9905.7324434389 3414.4046832579 0.0))
((0 . "LINE") (100 . "AcDbEntity") (8 . "MASONRY") (62 . 7) (370 . 13) (100 . "AcDbLine") (10 9830.3167420814
3050.5274434389 0.0) (11 9852.9411764706 3050.5274434389 0.0))
((0 . "LINE") (100 . "AcDbEntity") (8 . "MASONRY") (62 . 7) (370 . 13) (100 . "AcDbLine") (10 9834.086561086
3325.7918552036 0.0) (11 9992.45760181 3325.7918552036 0.0))
((0 . "LINE") (100 . "AcDbEntity") (8 . "MASONRY") (62 . 7) (370 . 13) (100 . "AcDbLine") (10 9905.7324434389
6114.2533936652 0.0) (11 9837.8591402715 6114.2533936652 0.0))
((0 . "LINE") (100 . "AcDbEntity") (8 . "MASONRY") (62 . 7) (370 . 13) (100 . "AcDbLine") (10 9837.8591402715
4408.1485067873 0.0) (11 9868.0232126697 4408.1485067873 0.0))
((0 . "LINE") (100 . "AcDbEntity") (8 . "MASONRY") (62 . 7) (370 . 13) (100 . "AcDbLine") (10 9841.628959276
2944.946979638 0.0) (11 9920.814479638 2944.946979638 0.0))
((0 . "LINE") (100 . "AcDbEntity") (8 . "MASONRY") (62 . 7) (370 . 13) (100 . "AcDbLine") (10 9841.628959276
2232.2772963801 0.0) (11 9898.1900452489 2232.2772963801 0.0))
((0 . "LINE") (100 . "AcDbEntity") (8 . "MASONRY") (62 . 7) (370 . 13) (100 . "AcDbLine") (10 9841.628959276
1238.6877828054 0.0) (11 9851.0562669683 1238.6877828054 0.0))
((0 . "LINE") (100 . "AcDbEntity") (8 . "MASONRY") (62 . 7) (370 . 13) (100 . "AcDbLine") (10 9860.4835746606
4268.4763914027 0.0) (11 9849.1713574661 4268.4763914027 0.0))
((0 . "LINE") (100 . "AcDbEntity") (8 . "MASONRY") (62 . 7) (370 . 13) (100 . "AcDbLine") (10 9851.0562669683
1251.8862895928 0.0) (11 9851.0562669683 1238.6877828054 0.0))
((0 . "LINE") (100 . "AcDbEntity") (8 . "MASONRY") (62 . 7) (370 . 13) (100 . "AcDbLine") (10 9901.9598642534
1238.6877828054 0.0) (11 9851.0562669683 1238.6877828054 0.0))
((0 . "LINE") (100 . "AcDbEntity") (8 . "MASONRY") (62 . 7) (370 . 13) (100 . "AcDbLine") (10 10237.556561086
477.0795022624 0.0) (11 9852.9453167421 477.0795022624 0.0))
((0 . "LINE") (100 . "AcDbEntity") (8 . "MASONRY") (62 . 7) (370 . 13) (100 . "AcDbLine") (10 9852.9453167421
477.0795022624 0.0) (11 9852.9453167421 490.195158371 0.0))
((0 . "LINE") (100 . "AcDbEntity") (8 . "MASONRY") (62 . 7) (370 . 13) (100 . "AcDbLine") (10 9879.3354298643
5908.7482352941 0.0) (11 9852.9411764706 5908.7482352941 0.0))
((0 . "LINE") (100 . "AcDbEntity") (8 . "MASONRY") (62 . 7) (370 . 13) (100 . "AcDbLine") (10 9858.5972850679
4660.6334841629 0.0) (11 9858.5972850679 4690.7989366516 0.0))
((0 . "LINE") (100 . "AcDbEntity") (8 . "MASONRY") (62 . 7) (370 . 13) (100 . "AcDbLine") (10 9911.3871719457
848.4162895928 0.0) (11 9852.9411764706 848.4162895928 0.0))
((0 . "LINE") (100 . "AcDbEntity") (8 . "MASONRY") (62 . 7) (370 . 13) (100 . "AcDbLine") (10 9852.9411764706
384.6153846154 0.0) (11 9852.9411764706 354.4485520362 0.0))
((0 . "LINE") (100 . "AcDbEntity") (8 . "MASONRY") (62 . 7) (370 . 13) (100 . "AcDbLine") (10 9852.9411764706
354.4485520362 0.0) (11 10098.0401357466 354.4485520362 0.0))
((0 . "LINE") (100 . "AcDbEntity") (8 . "MASONRY") (62 . 7) (370 . 13) (100 . "AcDbLine") (10 9947.2087330317
3288.0846945701 0.0) (11 9856.7109954751 3288.0846945701 0.0))
((0 . "LINE") (100 . "AcDbEntity") (8 . "MASONRY") (62 . 7) (370 . 13) (100 . "AcDbLine") (10 9862.3671040724
3190.0452488688 0.0) (11 9928.3568778281 3190.0452488688 0.0))
((0 . "LINE") (100 . "AcDbEntity") (8 . "MASONRY") (62 . 7) (370 . 13) (100 . "AcDbLine") (10 9862.3671040724
3148.5668891403 0.0) (11 9862.3671040724 3190.0452488688 0.0))
((0 . "LINE") (100 . "AcDbEntity") (8 . "MASONRY") (62 . 7) (370 . 13) (100 . "AcDbLine") (10 9932.1266968326
2175.7169004525 0.0) (11 9856.7109954751 2175.7169004525 0.0))
((0 . "LINE") (100 . "AcDbEntity") (8 . "MASONRY") (62 . 7) (370 . 13) (100 . "AcDbLine") (10 9856.7109954751
1738.913699095 0.0) (11 9877.3731900452 1738.913699095 0.0))
((0 . "LINE") (100 . "AcDbEntity") (8 . "MASONRY") (62 . 7) (370 . 13) (100 . "AcDbLine") (10 9877.3731900452
1738.913699095 0.0) (11 9877.3731900452 1753.3936651584 0.0))
((0 . "LINE") (100 . "AcDbEntity") (8 . "MASONRY") (62 . 7) (370 . 13) (100 . "AcDbLine") (10 9860.6672285068
4098.7938235294 0.0) (11 9860.6672285068 4066.819061086 0.0))
((0 . "LINE") (100 . "AcDbEntity") (8 . "MASONRY") (62 . 7) (370 . 13) (100 . "AcDbLine") (10 9860.6672285068
4066.819061086 0.0) (11 9973.6043665158 4066.819061086 0.0))
((0 . "LINE") (100 . "AcDbEntity") (8 . "MASONRY") (62 . 7) (370 . 13) (100 . "AcDbLine") (10 9973.6043665158
4066.819061086 0.0) (11 9973.6043665158 4079.9392081448 0.0))
((0 . "LINE") (100 . "AcDbEntity") (8 . "MASONRY") (62 . 7) (370 . 13) (100 . "AcDbLine") (10 9860.6672285068
4098.7938235294 0.0) (11 9977.4494457014 4098.7938235294 0.0))
((0 . "LINE") (100 . "AcDbEntity") (8 . "MASONRY") (62 . 7) (370 . 13) (100 . "AcDbLine") (10 9977.4494457014
4098.7938235294 0.0) (11 9977.4494457014 4137.7099547511 0.0))
((0 . "LINE") (100 . "AcDbEntity") (8 . "MASONRY") (62 . 7) (370 . 13) (100 . "AcDbLine") (10 9977.4494457014
4137.7099547511 0.0) (11 10000 4137.7099547511 0.0))
((0 . "LINE") (100 . "AcDbEntity") (8 . "MASONRY") (62 . 7) (370 . 13) (100 . "AcDbLine") (10 9860.4835746606
3753.7705090498 0.0) (11 9890.6476470588 3753.7705090498 0.0))
((0 . "LINE") (100 . "AcDbEntity") (8 . "MASONRY") (62 . 7) (370 . 13) (100 . "AcDbLine") (10 9860.4835746606
2110.4099773756 0.0) (11 9860.4835746606 2126.6968325792 0.0))
((0 . "LINE") (100 . "AcDbEntity") (8 . "MASONRY") (62 . 7) (370 . 13) (100 . "AcDbLine") (10 9860.4835746606
2110.4099773756 0.0) (11 9981.3007352941 2110.4099773756 0.0))
((0 . "LINE") (100 . "AcDbEntity") (8 . "MASONRY") (62 . 7) (370 . 13) (100 . "AcDbLine") (10 9981.3007352941
2110.4099773756 0.0) (11 9981.3007352941 2055.053020362 0.0))
((0 . "LINE") (100 . "AcDbEntity") (8 . "MASONRY") (62 . 7) (370 . 13) (100 . "AcDbLine") (10 9981.3007352941
2055.053020362 0.0) (11 9981.3007352941 2045.7037330317 0.0))
((0 . "LINE") (100 . "AcDbEntity") (8 . "MASONRY") (62 . 7) (370 . 13) (100 . "AcDbLine") (10 9981.3007352941
2045.7037330317 0.0) (11 10331.8241176471 2045.7037330317 0.0))
((0 . "LINE") (100 . "AcDbEntity") (8 . "MASONRY") (62 . 7) (370 . 13) (100 . "AcDbLine") (10 9860.4835746606
1858.9748190045 0.0) (11 9881.221719457 1858.9748190045 0.0))
((0 . "LINE") (100 . "AcDbEntity") (8 . "MASONRY") (62 . 7) (370 . 13) (100 . "AcDbLine") (10 9866.1383031674
4340.0435633484 0.0) (11 9866.1383031674 4377.8280542986 0.0))
((0 . "LINE") (100 . "AcDbEntity") (8 . "MASONRY") (62 . 7) (370 . 13) (100 . "AcDbLine") (10 9866.1383031674
4193.0613800905 0.0) (11 9866.1383031674 4136.5002941176 0.0))
((0 . "LINE") (100 . "AcDbEntity") (8 . "MASONRY") (62 . 7) (370 . 13) (100 . "AcDbLine") (10 9890.6476470588
2635.7466063348 0.0) (11 9864.2533936652 2635.7466063348 0.0))
((0 . "LINE") (100 . "AcDbEntity") (8 . "MASONRY") (62 . 7) (370 . 13) (100 . "AcDbLine") (10 9981.1453846154
1523.3795022624 0.0) (11 9864.2533936652 1523.3795022624 0.0))
((0 . "LINE") (100 . "AcDbEntity") (8 . "MASONRY") (62 . 7) (370 . 13) (100 . "AcDbLine") (10 9867.3693665158
537.3303167421 0.0) (11 9867.3693665158 572.9682239819 0.0))
((0 . "LINE") (100 . "AcDbEntity") (8 . "MASONRY") (62 . 7) (370 . 13) (100 . "AcDbLine") (10 9867.3693665158
572.9682239819 0.0) (11 9890.6476470588 572.9682239819 0.0))
((0 . "LINE") (100 . "AcDbEntity") (8 . "MASONRY") (62 . 7) (370 . 13) (100 . "AcDbLine") (10 9867.3693665158
537.3303167421 0.0) (11 9969.8331674208 537.3303167421 0.0))
((0 . "LINE") (100 . "AcDbEntity") (8 . "MASONRY") (62 . 7) (370 . 13) (100 . "AcDbLine") (10 9868.0232126697
4408.1485067873 0.0) (11 10109.3482126697 4408.1485067873 0.0))
((0 . "LINE") (100 . "AcDbEntity") (8 . "MASONRY") (62 . 7) (370 . 13) (100 . "AcDbLine") (10 10109.3482126697
4408.1485067873 0.0) (11 10109.3482126697 4445.7013574661 0.0))
((0 . "LINE") (100 . "AcDbEntity") (8 . "MASONRY") (62 . 7) (370 . 13) (100 . "AcDbLine") (10 9868.0232126697
4400.4524886878 0.0) (11 9868.0232126697 4408.1485067873 0.0))
((0 . "LINE") (100 . "AcDbEntity") (8 . "MASONRY") (62 . 7) (370 . 13) (100 . "AcDbLine") (10 9866.1383031674
4340.0435633484 0.0) (11 10060.3309049774 4340.0435633484 0.0))
((0 . "LINE") (100 . "AcDbEntity") (8 . "MASONRY") (62 . 7) (370 . 13) (100 . "AcDbLine") (10 9866.1383031674
4193.0613800905 0.0) (11 9988.6877828054 4193.0613800905 0.0))
((0 . "LINE") (100 . "AcDbEntity") (8 . "MASONRY") (62 . 7) (370 . 13) (100 . "AcDbLine") (10 9988.6877828054
4193.0613800905 0.0) (11 9988.6877828054 4211.9159954751 0.0))
((0 . "LINE") (100 . "AcDbEntity") (8 . "MASONRY") (62 . 7) (370 . 13) (100 . "AcDbLine") (10 9868.0232126697
2767.7227036199 0.0) (11 9920.814479638 2767.7227036199 0.0))
((0 . "LINE") (100 . "AcDbEntity") (8 . "MASONRY") (62 . 7) (370 . 13) (100 . "AcDbLine") (10 9871.7957918552
3059.9547511312 0.0) (11 10045.2488687783 3059.9547511312 0.0))
((0 . "LINE") (100 . "AcDbEntity") (8 . "MASONRY") (62 . 7) (370 . 13) (100 . "AcDbLine") (10 9879.3354298643
2405.7317533937 0.0) (11 9871.7957918552 2405.7317533937 0.0))
((0 . "LINE") (100 . "AcDbEntity") (8 . "MASONRY") (62 . 7) (370 . 13) (100 . "AcDbLine") (10 9877.450520362
6206.6363800905 0.0) (11 9966.0633484163 6206.6363800905 0.0))
((0 . "LINE") (100 . "AcDbEntity") (8 . "MASONRY") (62 . 7) (370 . 13) (100 . "AcDbLine") (10 9879.3354298643
5908.7482352941 0.0) (11 9879.3354298643 5878.582081448 0.0))
((0 . "LINE") (100 . "AcDbEntity") (8 . "MASONRY") (62 . 7) (370 . 13) (100 . "AcDbLine") (10 9879.3354298643
5908.7482352941 0.0) (11 9879.3354298643 5923.8309502262 0.0))
((0 . "LINE") (100 . "AcDbEntity") (8 . "MASONRY") (62 . 7) (370 . 13) (100 . "AcDbLine") (10 9924.5842986425
3557.6923076923 0.0) (11 9875.5656108597 3557.6923076923 0.0))
((0 . "LINE") (100 . "AcDbEntity") (8 . "MASONRY") (62 . 7) (370 . 13) (100 . "AcDbLine") (10 9879.3354298643
5833.3332126697 0.0) (11 9879.3354298643 5855.9576470588 0.0))
((0 . "LINE") (100 . "AcDbEntity") (8 . "MASONRY") (62 . 7) (370 . 13) (100 . "AcDbLine") (10 10105.5797737557
5833.3332126697 0.0) (11 9879.3354298643 5833.3332126697 0.0))
((0 . "LINE") (100 . "AcDbEntity") (8 . "MASONRY") (62 . 7) (370 . 13) (100 . "AcDbLine") (10 9884.9915384615
3714.178438914 0.0) (11 9884.9915384615 3691.5540045249 0.0))
((0 . "LINE") (100 . "AcDbEntity") (8 . "MASONRY") (62 . 7) (370 . 13) (100 . "AcDbLine") (10 9879.3354298643
2488.6877828054 0.0) (11 9879.3354298643 2458.5216402715 0.0))
((0 . "LINE") (100 . "AcDbEntity") (8 . "MASONRY") (62 . 7) (370 . 13) (100 . "AcDbLine") (10 9879.3354298643
2405.7317533937 0.0) (11 9879.3354298643 2458.5216402715 0.0))
((0 . "LINE") (100 . "AcDbEntity") (8 . "MASONRY") (62 . 7) (370 . 13) (100 . "AcDbLine") (10 9881.221719457
1828.8086764706 0.0) (11 9881.221719457 1858.9748190045 0.0))
((0 . "LINE") (100 . "AcDbEntity") (8 . "MASONRY") (62 . 7) (370 . 13) (100 . "AcDbLine") (10 9941.5540045249
1858.9748190045 0.0) (11 9881.221719457 1858.9748190045 0.0))
((0 . "LINE") (100 . "AcDbEntity") (8 . "MASONRY") (62 . 7) (370 . 13) (100 . "AcDbLine") (10 9901.9598642534
1259.4259276018 0.0) (11 9879.3354298643 1259.4259276018 0.0))
((0 . "LINE") (100 . "AcDbEntity") (8 . "MASONRY") (62 . 7) (370 . 13) (100 . "AcDbLine") (10 9884.9155882353
5248.8687782805 0.0) (11 9969.8331674208 5248.8687782805 0.0))
((0 . "LINE") (100 . "AcDbEntity") (8 . "MASONRY") (62 . 7) (370 . 13) (100 . "AcDbLine") (10 9888.7627375566
3974.3594343891 0.0) (11 9888.7627375566 3989.4414705882 0.0))
((0 . "LINE") (100 . "AcDbEntity") (8 . "MASONRY") (62 . 7) (370 . 13) (100 . "AcDbLine") (10 9977.3755656109
4021.6416628959 0.0) (11 9977.3755656109 3989.4414705882 0.0))
((0 . "LINE") (100 . "AcDbEntity") (8 . "MASONRY") (62 . 7) (370 . 13) (100 . "AcDbLine") (10 9977.3755656109
3989.4414705882 0.0) (11 9888.7627375566 3989.4414705882 0.0))
((0 . "LINE") (100 . "AcDbEntity") (8 . "MASONRY") (62 . 7) (370 . 13) (100 . "AcDbLine") (10 9888.7627375566
3863.1221719457 0.0) (11 9888.7627375566 3804.6761764706 0.0))
((0 . "LINE") (100 . "AcDbEntity") (8 . "MASONRY") (62 . 7) (370 . 13) (100 . "AcDbLine") (10 9879.3354298643
2405.7317533937 0.0) (11 9898.1900452489 2405.7317533937 0.0))
((0 . "LINE") (100 . "AcDbEntity") (8 . "MASONRY") (62 . 7) (370 . 13) (100 . "AcDbLine") (10 9920.814479638
1163.2734615385 0.0) (11 9886.8778280543 1163.2734615385 0.0))
((0 . "LINE") (100 . "AcDbEntity") (8 . "MASONRY") (62 . 7) (370 . 13) (100 . "AcDbLine") (10 9888.7627375566
1010.5571493213 0.0) (11 9888.7627375566 991.7052941176 0.0))
((0 . "LINE") (100 . "AcDbEntity") (8 . "MASONRY") (62 . 7) (370 . 13) (100 . "AcDbLine") (10 9890.6476470588
4624.8112330317 0.0) (11 9992.45760181 4624.8112330317 0.0))
((0 . "LINE") (100 . "AcDbEntity") (8 . "MASONRY") (62 . 7) (370 . 13) (100 . "AcDbLine") (10 10143.2876244344
3863.1221719457 0.0) (11 10116.8919909502 3863.1221719457 0.0))
((0 . "LINE") (100 . "AcDbEntity") (8 . "MASONRY") (62 . 7) (370 . 13) (100 . "AcDbLine") (10 10116.8919909502
3863.1221719457 0.0) (11 9888.7627375566 3863.1221719457 0.0))
((0 . "LINE") (100 . "AcDbEntity") (8 . "MASONRY") (62 . 7) (370 . 13) (100 . "AcDbLine") (10 9888.7627375566
991.7052941176 0.0) (11 9898.1900452489 991.7052941176 0.0))
((0 . "LINE") (100 . "AcDbEntity") (8 . "MASONRY") (62 . 7) (370 . 13) (100 . "AcDbLine") (10 9901.9598642534
5520.3619909502 0.0) (11 9901.9598642534 5527.9030090498 0.0))
((0 . "LINE") (100 . "AcDbEntity") (8 . "MASONRY") (62 . 7) (370 . 13) (100 . "AcDbLine") (10 9898.1900452489
5478.884321267 0.0) (11 9898.1900452489 5439.2908710407 0.0))
((0 . "LINE") (100 . "AcDbEntity") (8 . "MASONRY") (62 . 7) (370 . 13) (100 . "AcDbLine") (10 10075.4157013575
5439.2908710407 0.0) (11 9898.1900452489 5439.2908710407 0.0))
((0 . "LINE") (100 . "AcDbEntity") (8 . "MASONRY") (62 . 7) (370 . 13) (100 . "AcDbLine") (10 9950.9813122172
5096.1538461538 0.0) (11 9898.1900452489 5096.1538461538 0.0))
((0 . "LINE") (100 . "AcDbEntity") (8 . "MASONRY") (62 . 7) (370 . 13) (100 . "AcDbLine") (10 9920.814479638
2835.5960067873 0.0) (11 9898.1900452489 2835.5960067873 0.0))
((0 . "LINE") (100 . "AcDbEntity") (8 . "MASONRY") (62 . 7) (370 . 13) (100 . "AcDbLine") (10 9928.3568778281
5527.9030090498 0.0) (11 9901.9598642534 5527.9030090498 0.0))
((0 . "LINE") (100 . "AcDbEntity") (8 . "MASONRY") (62 . 7) (370 . 13) (100 . "AcDbLine") (10 9901.9598642534
5550.5274434389 0.0) (11 9901.9598642534 5527.9030090498 0.0))
((0 . "LINE") (100 . "AcDbEntity") (8 . "MASONRY") (62 . 7) (370 . 13) (100 . "AcDbLine") (10 9901.9598642534
1259.4259276018 0.0) (11 9901.9598642534 1238.6877828054 0.0))
((0 . "LINE") (100 . "AcDbEntity") (8 . "MASONRY") (62 . 7) (370 . 13) (100 . "AcDbLine") (10 9901.9598642534
1259.4259276018 0.0) (11 9917.0446606335 1259.4259276018 0.0))
((0 . "LINE") (100 . "AcDbEntity") (8 . "MASONRY") (62 . 7) (370 . 13) (100 . "AcDbLine") (10 9913.272081448
1238.6877828054 0.0) (11 9901.9598642534 1238.6877828054 0.0))
((0 . "LINE") (100 . "AcDbEntity") (8 . "MASONRY") (62 . 7) (370 . 13) (100 . "AcDbLine") (10 9905.7324434389
4262.8202828054 0.0) (11 10018.8546153846 4262.8202828054 0.0))
((0 . "LINE") (100 . "AcDbEntity") (8 . "MASONRY") (62 . 7) (370 . 13) (100 . "AcDbLine") (10 9911.3871719457
810.7098190045 0.0) (11 9905.7324434389 810.7098190045 0.0))
((0 . "LINE") (100 . "AcDbEntity") (8 . "MASONRY") (62 . 7) (370 . 13) (100 . "AcDbLine") (10 9911.3871719457
4856.7123755656 0.0) (11 9911.3871719457 4892.5339366516 0.0))
((0 . "LINE") (100 . "AcDbEntity") (8 . "MASONRY") (62 . 7) (370 . 13) (100 . "AcDbLine") (10 9924.5842986425
3150.4524886878 0.0) (11 9909.5022624434 3150.4524886878 0.0))
((0 . "LINE") (100 . "AcDbEntity") (8 . "MASONRY") (62 . 7) (370 . 13) (100 . "AcDbLine") (10 9911.3871719457
810.7098190045 0.0) (11 9911.3871719457 848.4162895928 0.0))
((0 . "LINE") (100 . "AcDbEntity") (8 . "MASONRY") (62 . 7) (370 . 13) (100 . "AcDbLine") (10 9911.3871719457
848.4162895928 0.0) (11 10131.9767873303 848.4162895928 0.0))
((0 . "LINE") (100 . "AcDbEntity") (8 . "MASONRY") (62 . 7) (370 . 13) (100 . "AcDbLine") (10 9909.5022624434
573.1532579186 0.0) (11 9924.5842986425 573.1532579186 0.0))
((0 . "LINE") (100 . "AcDbEntity") (8 . "MASONRY") (62 . 7) (370 . 13) (100 . "AcDbLine") (10 10128.2042081448
4892.5339366516 0.0) (11 9911.3871719457 4892.5339366516 0.0))
((0 . "LINE") (100 . "AcDbEntity") (8 . "MASONRY") (62 . 7) (370 . 13) (100 . "AcDbLine") (10 9913.272081448
2334.0872511312 0.0) (11 10191.3659276018 2334.0872511312 0.0))
((0 . "LINE") (100 . "AcDbEntity") (8 . "MASONRY") (62 . 7) (370 . 13) (100 . "AcDbLine") (10 9911.3871719457
810.7098190045 0.0) (11 9992.45760181 810.7098190045 0.0))
((0 . "LINE") (100 . "AcDbEntity") (8 . "MASONRY") (62 . 7) (370 . 13) (100 . "AcDbLine") (10 9920.814479638
2835.5960067873 0.0) (11 9920.814479638 2767.7227036199 0.0))
((0 . "LINE") (100 . "AcDbEntity") (8 . "MASONRY") (62 . 7) (370 . 13) (100 . "AcDbLine") (10 9920.814479638
2835.5960067873 0.0) (11 9920.814479638 2944.946979638 0.0))
((0 . "LINE") (100 . "AcDbEntity") (8 . "MASONRY") (62 . 7) (370 . 13) (100 . "AcDbLine") (10 9993.0596719457
2767.7227036199 0.0) (11 9920.814479638 2767.7227036199 0.0))
((0 . "LINE") (100 . "AcDbEntity") (8 . "MASONRY") (62 . 7) (370 . 13) (100 . "AcDbLine") (10 9990.5726923077
2628.20489819 0.0) (11 9920.814479638 2628.20489819 0.0))
((0 . "LINE") (100 . "AcDbEntity") (8 . "MASONRY") (62 . 7) (370 . 13) (100 . "AcDbLine") (10 9920.814479638
1802.4137330317 0.0) (11 10150.8286425339 1802.4137330317 0.0))
((0 . "LINE") (100 . "AcDbEntity") (8 . "MASONRY") (62 . 7) (370 . 13) (100 . "AcDbLine") (10 10105.5797737557
2944.946979638 0.0) (11 9920.814479638 2944.946979638 0.0))
((0 . "LINE") (100 . "AcDbEntity") (8 . "MASONRY") (62 . 7) (370 . 13) (100 . "AcDbLine") (10 9924.5842986425
2269.9851470588 0.0) (11 9990.5726923077 2269.9851470588 0.0))
((0 . "LINE") (100 . "AcDbEntity") (8 . "MASONRY") (62 . 7) (370 . 13) (100 . "AcDbLine") (10 9937.7054751131
1987.1797171946 0.0) (11 9937.7054751131 1936.274739819 0.0))
((0 . "LINE") (100 . "AcDbEntity") (8 . "MASONRY") (62 . 7) (370 . 13) (100 . "AcDbLine") (10 9937.7054751131
1936.274739819 0.0) (11 9924.5842986425 1936.274739819 0.0))
((0 . "LINE") (100 . "AcDbEntity") (8 . "MASONRY") (62 . 7) (370 . 13) (100 . "AcDbLine") (10 9924.5842986425
955.8823529412 0.0) (11 9988.6877828054 955.8823529412 0.0))
((0 . "LINE") (100 . "AcDbEntity") (8 . "MASONRY") (62 . 7) (370 . 13) (100 . "AcDbLine") (10 9939.6690950226
1089.7426696833 0.0) (11 9932.1266968326 1089.7426696833 0.0))
((0 . "LINE") (100 . "AcDbEntity") (8 . "MASONRY") (62 . 7) (370 . 13) (100 . "AcDbLine") (10 9935.8965158371
3406.8622850679 0.0) (11 9992.45760181 3406.8622850679 0.0))
((0 . "LINE") (100 . "AcDbEntity") (8 . "MASONRY") (62 . 7) (370 . 13) (100 . "AcDbLine") (10 9981.1453846154
2405.7317533937 0.0) (11 9935.8965158371 2405.7317533937 0.0))
((0 . "LINE") (100 . "AcDbEntity") (8 . "MASONRY") (62 . 7) (370 . 13) (100 . "AcDbLine") (10 9937.7054751131
1987.1797171946 0.0) (11 9981.1453846154 1987.1797171946 0.0))
((0 . "LINE") (100 . "AcDbEntity") (8 . "MASONRY") (62 . 7) (370 . 13) (100 . "AcDbLine") (10 9996.2301809955
991.7052941176 0.0) (11 9935.8965158371 991.7052941176 0.0))
((0 . "LINE") (100 . "AcDbEntity") (8 . "MASONRY") (62 . 7) (370 . 13) (100 . "AcDbLine") (10 9941.5540045249
1858.9748190045 0.0) (11 9941.5540045249 1892.910780543 0.0))
((0 . "LINE") (100 . "AcDbEntity") (8 . "MASONRY") (62 . 7) (370 . 13) (100 . "AcDbLine") (10 9939.6690950226
1227.3755656109 0.0) (11 9954.7511312217 1227.3755656109 0.0))
((0 . "LINE") (100 . "AcDbEntity") (8 . "MASONRY") (62 . 7) (370 . 13) (100 . "AcDbLine") (10 9941.5540045249
1858.9748190045 0.0) (11 10154.6012217195 1858.9748190045 0.0))
((0 . "LINE") (100 . "AcDbEntity") (8 . "MASONRY") (62 . 7) (370 . 13) (100 . "AcDbLine") (10 9943.4389140272
86.7265384615 0.0) (11 9950.9813122172 86.7265384615 0.0))
((0 . "LINE") (100 . "AcDbEntity") (8 . "MASONRY") (62 . 7) (370 . 13) (100 . "AcDbLine") (10 9949.0950226244
4785.0678733032 0.0) (11 9949.0950226244 4769.9844570136 0.0))
((0 . "LINE") (100 . "AcDbEntity") (8 . "MASONRY") (62 . 7) (370 . 13) (100 . "AcDbLine") (10 10105.5797737557
1342.5310972851 0.0) (11 10086.727918552 1342.5310972851 0.0))
((0 . "LINE") (100 . "AcDbEntity") (8 . "MASONRY") (62 . 7) (370 . 13) (100 . "AcDbLine") (10 10086.727918552
1342.5310972851 0.0) (11 9947.2087330317 1342.5310972851 0.0))
((0 . "LINE") (100 . "AcDbEntity") (8 . "MASONRY") (62 . 7) (370 . 13) (100 . "AcDbLine") (10 9952.8689819005
177.2256561086 0.0) (11 9952.8689819005 121.2666402715 0.0))
((0 . "LINE") (100 . "AcDbEntity") (8 . "MASONRY") (62 . 7) (370 . 13) (100 . "AcDbLine") (10 9952.8689819005
121.2666402715 0.0) (11 10128.2042081448 121.2666402715 0.0))
((0 . "LINE") (100 . "AcDbEntity") (8 . "MASONRY") (62 . 7) (370 . 13) (100 . "AcDbLine") (10 9952.8689819005
177.2256561086 0.0) (11 10060.3309049774 177.2256561086 0.0))
((0 . "LINE") (100 . "AcDbEntity") (8 . "MASONRY") (62 . 7) (370 . 13) (100 . "AcDbLine") (10 9949.0950226244
4785.0678733032 0.0) (11 10148.9437330317 4785.0678733032 0.0))
((0 . "LINE") (100 . "AcDbEntity") (8 . "MASONRY") (62 . 7) (370 . 13) (100 . "AcDbLine") (10 10152.7149321267
1185.2958257919 0.0) (11 9971.2679072398 1185.2958257919 0.0))
((0 . "LINE") (100 . "AcDbEntity") (8 . "MASONRY") (62 . 7) (370 . 13) (100 . "AcDbLine") (10 9971.2679072398
1185.2958257919 0.0) (11 9971.2679072398 1099.1713574661 0.0))
((0 . "LINE") (100 . "AcDbEntity") (8 . "MASONRY") (62 . 7) (370 . 13) (100 . "AcDbLine") (10 9971.2679072398
1099.1713574661 0.0) (11 9950.9813122172 1099.1713574661 0.0))
((0 . "LINE") (100 . "AcDbEntity") (8 . "MASONRY") (62 . 7) (370 . 13) (100 . "AcDbLine") (10 9950.9813122172
575.0381674208 0.0) (11 9969.8331674208 575.0381674208 0.0))
((0 . "LINE") (100 . "AcDbEntity") (8 . "MASONRY") (62 . 7) (370 . 13) (100 . "AcDbLine") (10 9950.9813122172
256.4111764706 0.0) (11 9967.9482579186 256.4111764706 0.0))
((0 . "LINE") (100 . "AcDbEntity") (8 . "MASONRY") (62 . 7) (370 . 13) (100 . "AcDbLine") (10 9961.0093099548
5642.910780543 0.0) (11 9961.0093099548 5678.7330316742 0.0))
((0 . "LINE") (100 . "AcDbEntity") (8 . "MASONRY") (62 . 7) (370 . 13) (100 . "AcDbLine") (10 9961.0093099548
5678.7330316742 0.0) (11 9961.0093099548 5731.5232579186 0.0))
((0 . "LINE") (100 . "AcDbEntity") (8 . "MASONRY") (62 . 7) (370 . 13) (100 . "AcDbLine") (10 9966.0633484163
6114.2533936652 0.0) (11 9958.5209502262 6114.2533936652 0.0))
((0 . "LINE") (100 . "AcDbEntity") (8 . "MASONRY") (62 . 7) (370 . 13) (100 . "AcDbLine") (10 9958.5209502262
50.9049773756 0.0) (11 9966.0633484163 50.9049773756 0.0))
((0 . "LINE") (100 . "AcDbEntity") (8 . "MASONRY") (62 . 7) (370 . 13) (100 . "AcDbLine") (10 10248.8687782805
4973.6043665158 0.0) (11 9962.2935294118 4973.6043665158 0.0))
((0 . "LINE") (100 . "AcDbEntity") (8 . "MASONRY") (62 . 7) (370 . 13) (100 . "AcDbLine") (10 10196.0775113122
3707.9195701357 0.0) (11 9946.0039140272 3707.9195701357 0.0))
((0 . "LINE") (100 . "AcDbEntity") (8 . "MASONRY") (62 . 7) (370 . 13) (100 . "AcDbLine") (10 9946.0039140272
3707.9195701357 0.0) (11 9946.0039140272 3689.7453846154 0.0))
((0 . "LINE") (100 . "AcDbEntity") (8 . "MASONRY") (62 . 7) (370 . 13) (100 . "AcDbLine") (10 9946.0039140272
3689.7453846154 0.0) (11 9962.2935294118 3689.7453846154 0.0))
((0 . "LINE") (100 . "AcDbEntity") (8 . "MASONRY") (62 . 7) (370 . 13) (100 . "AcDbLine") (10 9966.0633484163
6114.2533936652 0.0) (11 9966.0633484163 6206.6363800905 0.0))
((0 . "LINE") (100 . "AcDbEntity") (8 . "MASONRY") (62 . 7) (370 . 13) (100 . "AcDbLine") (10 9998.1150904977
6206.6363800905 0.0) (11 9966.0633484163 6206.6363800905 0.0))
((0 . "LINE") (100 . "AcDbEntity") (8 . "MASONRY") (62 . 7) (370 . 13) (100 . "AcDbLine") (10 9966.0633484163
6114.2533936652 0.0) (11 9966.0633484163 6093.6754298643 0.0))
((0 . "LINE") (100 . "AcDbEntity") (8 . "MASONRY") (62 . 7) (370 . 13) (100 . "AcDbLine") (10 9966.0633484163
6093.6754298643 0.0) (11 10194.19260181 6093.6754298643 0.0))
((0 . "LINE") (100 . "AcDbEntity") (8 . "MASONRY") (62 . 7) (370 . 13) (100 . "AcDbLine") (10 9961.0093099548
5642.910780543 0.0) (11 9961.0093099548 5546.7576244344 0.0))
((0 . "LINE") (100 . "AcDbEntity") (8 . "MASONRY") (62 . 7) (370 . 13) (100 . "AcDbLine") (10 9961.0093099548
5546.7576244344 0.0) (11 9969.8331674208 5546.7576244344 0.0))
((0 . "LINE") (100 . "AcDbEntity") (8 . "MASONRY") (62 . 7) (370 . 13) (100 . "AcDbLine") (10 9969.8331674208
5546.7576244344 0.0) (11 10109.3509728507 5546.7576244344 0.0))
((0 . "LINE") (100 . "AcDbEntity") (8 . "MASONRY") (62 . 7) (370 . 13) (100 . "AcDbLine") (10 9961.0093099548
5642.910780543 0.0) (11 10056.5610859729 5642.910780543 0.0))
((0 . "LINE") (100 . "AcDbEntity") (8 . "MASONRY") (62 . 7) (370 . 13) (100 . "AcDbLine") (10 9969.8331674208
5199.8487104072 0.0) (11 9969.8331674208 5248.8687782805 0.0))
((0 . "LINE") (100 . "AcDbEntity") (8 . "MASONRY") (62 . 7) (370 . 13) (100 . "AcDbLine") (10 10022.6244343891
5248.8687782805 0.0) (11 9969.8331674208 5248.8687782805 0.0))
((0 . "LINE") (100 . "AcDbEntity") (8 . "MASONRY") (62 . 7) (370 . 13) (100 . "AcDbLine") (10 9969.8345475113
3159.8791063348 0.0) (11 9969.8345475113 3148.5668891403 0.0))
((0 . "LINE") (100 . "AcDbEntity") (8 . "MASONRY") (62 . 7) (370 . 13) (100 . "AcDbLine") (10 9966.0633484163
2865.761459276 0.0) (11 10128.2042081448 2865.761459276 0.0))
((0 . "LINE") (100 . "AcDbEntity") (8 . "MASONRY") (62 . 7) (370 . 13) (100 . "AcDbLine") (10 9969.8331674208
575.0381674208 0.0) (11 9969.8331674208 537.3303167421 0.0))
((0 . "LINE") (100 . "AcDbEntity") (8 . "MASONRY") (62 . 7) (370 . 13) (100 . "AcDbLine") (10 9969.8331674208
575.0381674208 0.0) (11 9969.8331674208 697.5876470588 0.0))
((0 . "LINE") (100 . "AcDbEntity") (8 . "MASONRY") (62 . 7) (370 . 13) (100 . "AcDbLine") (10 10098.0401357466
256.4111764706 0.0) (11 9967.9482579186 256.4111764706 0.0))
((0 . "LINE") (100 . "AcDbEntity") (8 . "MASONRY") (62 . 7) (370 . 13) (100 . "AcDbLine") (10 9967.9482579186
275.2630316742 0.0) (11 9967.9482579186 256.4111764706 0.0))
((0 . "LINE") (100 . "AcDbEntity") (8 . "MASONRY") (62 . 7) (370 . 13) (100 . "AcDbLine") (10 9969.8331674208
6255.6561085973 0.0) (11 9993.6624208145 6255.6561085973 0.0))
((0 . "LINE") (100 . "AcDbEntity") (8 . "MASONRY") (62 . 7) (370 . 13) (100 . "AcDbLine") (10 9971.7194570136
6014.3286877828 0.0) (11 10011.3122171946 6014.3286877828 0.0))
((0 . "LINE") (100 . "AcDbEntity") (8 . "MASONRY") (62 . 7) (370 . 13) (100 . "AcDbLine") (10 9971.7194570136
6014.3286877828 0.0) (11 9971.7194570136 6074.6606334842 0.0))
((0 . "LINE") (100 . "AcDbEntity") (8 . "MASONRY") (62 . 7) (370 . 13) (100 . "AcDbLine") (10 9969.8331674208
5199.8487104072 0.0) (11 9969.8331674208 5180.9954751131 0.0))
((0 . "LINE") (100 . "AcDbEntity") (8 . "MASONRY") (62 . 7) (370 . 13) (100 . "AcDbLine") (10 9969.8331674208
3563.3484162896 0.0) (11 9988.6877828054 3563.3484162896 0.0))
((0 . "LINE") (100 . "AcDbEntity") (8 . "MASONRY") (62 . 7) (370 . 13) (100 . "AcDbLine") (10 9981.1453846154
1606.334841629 0.0) (11 9981.1453846154 1591.2514253394 0.0))
((0 . "LINE") (100 . "AcDbEntity") (8 . "MASONRY") (62 . 7) (370 . 13) (100 . "AcDbLine") (10 9988.6877828054
5199.8487104072 0.0) (11 9969.8331674208 5199.8487104072 0.0))
((0 . "LINE") (100 . "AcDbEntity") (8 . "MASONRY") (62 . 7) (370 . 13) (100 . "AcDbLine") (10 9981.1467647059
2213.424061086 0.0) (11 9981.1467647059 2232.2772963801 0.0))
((0 . "LINE") (100 . "AcDbEntity") (8 . "MASONRY") (62 . 7) (370 . 13) (100 . "AcDbLine") (10 10165.913438914
537.3303167421 0.0) (11 9969.8331674208 537.3303167421 0.0))
((0 . "LINE") (100 . "AcDbEntity") (8 . "MASONRY") (62 . 7) (370 . 13) (100 . "AcDbLine") (10 9977.3755656109
4726.6211877828 0.0) (11 10011.3122171946 4726.6211877828 0.0))
((0 . "LINE") (100 . "AcDbEntity") (8 . "MASONRY") (62 . 7) (370 . 13) (100 . "AcDbLine") (10 9977.3755656109
4021.6416628959 0.0) (11 9977.3755656109 4030.920520362 0.0))
((0 . "LINE") (100 . "AcDbEntity") (8 . "MASONRY") (62 . 7) (370 . 13) (100 . "AcDbLine") (10 9977.3755656109
4021.6416628959 0.0) (11 10318.7788914027 4021.6416628959 0.0))
((0 . "LINE") (100 . "AcDbEntity") (8 . "MASONRY") (62 . 7) (370 . 13) (100 . "AcDbLine") (10 10318.7788914027
4021.6416628959 0.0) (11 10318.7788914027 3989.4414705882 0.0))
((0 . "LINE") (100 . "AcDbEntity") (8 . "MASONRY") (62 . 7) (370 . 13) (100 . "AcDbLine") (10 9977.3755656109
3684.0116063348 0.0) (11 9984.9179638009 3684.0116063348 0.0))
((0 . "LINE") (100 . "AcDbEntity") (8 . "MASONRY") (62 . 7) (370 . 13) (100 . "AcDbLine") (10 9983.0316742081
5064.1021040724 0.0) (11 9983.0316742081 4996.228800905 0.0))
((0 . "LINE") (100 . "AcDbEntity") (8 . "MASONRY") (62 . 7) (370 . 13) (100 . "AcDbLine") (10 9981.1453846154
2021.1163687783 0.0) (11 9981.1453846154 1987.1797171946 0.0))
((0 . "LINE") (100 . "AcDbEntity") (8 . "MASONRY") (62 . 7) (370 . 13) (100 . "AcDbLine") (10 9981.1453846154
1987.1797171946 0.0) (11 10041.4790497738 1987.1797171946 0.0))
((0 . "LINE") (100 . "AcDbEntity") (8 . "MASONRY") (62 . 7) (370 . 13) (100 . "AcDbLine") (10 9981.1453846154
1564.8557918552 0.0) (11 9981.1453846154 1591.2514253394 0.0))
((0 . "LINE") (100 . "AcDbEntity") (8 . "MASONRY") (62 . 7) (370 . 13) (100 . "AcDbLine") (10 9981.1453846154
1591.2514253394 0.0) (11 10124.4343891403 1591.2514253394 0.0))
((0 . "LINE") (100 . "AcDbEntity") (8 . "MASONRY") (62 . 7) (370 . 13) (100 . "AcDbLine") (10 9981.1453846154
1523.3795022624 0.0) (11 10064.1034841629 1523.3795022624 0.0))
((0 . "LINE") (100 . "AcDbEntity") (8 . "MASONRY") (62 . 7) (370 . 13) (100 . "AcDbLine") (10 9981.1453846154
1523.3795022624 0.0) (11 9981.1453846154 1515.8371040724 0.0))
((0 . "LINE") (100 . "AcDbEntity") (8 . "MASONRY") (62 . 7) (370 . 13) (100 . "AcDbLine") (10 9981.1453846154
1436.6515837104 0.0) (11 9981.1453846154 1493.2126696833 0.0))
((0 . "LINE") (100 . "AcDbEntity") (8 . "MASONRY") (62 . 7) (370 . 13) (100 . "AcDbLine") (10 9981.1453846154
1436.6515837104 0.0) (11 10071.6431221719 1436.6515837104 0.0))
((0 . "LINE") (100 . "AcDbEntity") (8 . "MASONRY") (62 . 7) (370 . 13) (100 . "AcDbLine") (10 9992.45760181
4566.3645475113 0.0) (11 9984.9179638009 4566.3645475113 0.0))
((0 . "LINE") (100 . "AcDbEntity") (8 . "MASONRY") (62 . 7) (370 . 13) (100 . "AcDbLine") (10 9984.9179638009
3672.6993891403 0.0) (11 9984.9179638009 3684.0116063348 0.0))
((0 . "LINE") (100 . "AcDbEntity") (8 . "MASONRY") (62 . 7) (370 . 13) (100 . "AcDbLine") (10 10018.8546153846
3684.0116063348 0.0) (11 9984.9179638009 3684.0116063348 0.0))
((0 . "LINE") (100 . "AcDbEntity") (8 . "MASONRY") (62 . 7) (370 . 13) (100 . "AcDbLine") (10 9988.6877828054
3597.2850678733 0.0) (11 9988.6877828054 3563.3484162896 0.0))
((0 . "LINE") (100 . "AcDbEntity") (8 . "MASONRY") (62 . 7) (370 . 13) (100 . "AcDbLine") (10 9988.6877828054
3597.2850678733 0.0) (11 9988.6877828054 3608.5972850679 0.0))
((0 . "LINE") (100 . "AcDbEntity") (8 . "MASONRY") (62 . 7) (370 . 13) (100 . "AcDbLine") (10 9996.2301809955
1266.9683257919 0.0) (11 9984.9179638009 1266.9683257919 0.0))
((0 . "LINE") (100 . "AcDbEntity") (8 . "MASONRY") (62 . 7) (370 . 13) (100 . "AcDbLine") (10 9993.6624208145
6255.6561085973 0.0) (11 9993.6624208145 6240.5730316742 0.0))
((0 . "LINE") (100 . "AcDbEntity") (8 . "MASONRY") (62 . 7) (370 . 13) (100 . "AcDbLine") (10 10267.7233936652
6308.3690158371 0.0) (11 10011.3122171946 6308.3690158371 0.0))
((0 . "LINE") (100 . "AcDbEntity") (8 . "MASONRY") (62 . 7) (370 . 13) (100 . "AcDbLine") (10 10011.3122171946
6308.3690158371 0.0) (11 9993.6624208145 6308.3690158371 0.0))
((0 . "LINE") (100 . "AcDbEntity") (8 . "MASONRY") (62 . 7) (370 . 13) (100 . "AcDbLine") (10 9993.6624208145
6308.3690158371 0.0) (11 9993.6624208145 6255.6561085973 0.0))
((0 . "LINE") (100 . "AcDbEntity") (8 . "MASONRY") (62 . 7) (370 . 13) (100 . "AcDbLine") (10 9992.45760181
4596.5313800905 0.0) (11 9992.45760181 4624.8112330317 0.0))
((0 . "LINE") (100 . "AcDbEntity") (8 . "MASONRY") (62 . 7) (370 . 13) (100 . "AcDbLine") (10 9988.6877828054
4234.5404298643 0.0) (11 9988.6877828054 4211.9159954751 0.0))
((0 . "LINE") (100 . "AcDbEntity") (8 . "MASONRY") (62 . 7) (370 . 13) (100 . "AcDbLine") (10 10022.6244343891
2628.20489819 0.0) (11 9990.5726923077 2628.20489819 0.0))
((0 . "LINE") (100 . "AcDbEntity") (8 . "MASONRY") (62 . 7) (370 . 13) (100 . "AcDbLine") (10 9990.5726923077
2677.2249660633 0.0) (11 9990.5726923077 2628.20489819 0.0))
((0 . "LINE") (100 . "AcDbEntity") (8 . "MASONRY") (62 . 7) (370 . 13) (100 . "AcDbLine") (10 9990.5726923077
2258.6729298643 0.0) (11 9990.5726923077 2269.9851470588 0.0))
((0 . "LINE") (100 . "AcDbEntity") (8 . "MASONRY") (62 . 7) (370 . 13) (100 . "AcDbLine") (10 10003.7698190045
2269.9851470588 0.0) (11 9990.5726923077 2269.9851470588 0.0))
((0 . "LINE") (100 . "AcDbEntity") (8 . "MASONRY") (62 . 7) (370 . 13) (100 . "AcDbLine") (10 9988.6877828054
2198.3406447964 0.0) (11 9988.6877828054 2175.7162104072 0.0))
((0 . "LINE") (100 . "AcDbEntity") (8 . "MASONRY") (62 . 7) (370 . 13) (100 . "AcDbLine") (10 9992.45760181
4634.2378506787 0.0) (11 9992.45760181 4679.486719457 0.0))
((0 . "LINE") (100 . "AcDbEntity") (8 . "MASONRY") (62 . 7) (370 . 13) (100 . "AcDbLine") (10 9992.45760181
4634.2378506787 0.0) (11 9992.45760181 4624.8112330317 0.0))
((0 . "LINE") (100 . "AcDbEntity") (8 . "MASONRY") (62 . 7) (370 . 13) (100 . "AcDbLine") (10 10139.5164253394
4211.9159954751 0.0) (11 9988.6877828054 4211.9159954751 0.0))
((0 . "LINE") (100 . "AcDbEntity") (8 . "MASONRY") (62 . 7) (370 . 13) (100 . "AcDbLine") (10 9988.6877828054
3563.3484162896 0.0) (11 10000 3563.3484162896 0.0))
((0 . "LINE") (100 . "AcDbEntity") (8 . "MASONRY") (62 . 7) (370 . 13) (100 . "AcDbLine") (10 9992.45760181
3288.0846945701 0.0) (11 9992.45760181 3325.7918552036 0.0))
((0 . "LINE") (100 . "AcDbEntity") (8 . "MASONRY") (62 . 7) (370 . 13) (100 . "AcDbLine") (10 10199.8500904977
3325.7918552036 0.0) (11 9992.45760181 3325.7918552036 0.0))
((0 . "LINE") (100 . "AcDbEntity") (8 . "MASONRY") (62 . 7) (370 . 13) (100 . "AcDbLine") (10 9992.45760181
3288.0846945701 0.0) (11 9992.45760181 3186.274739819 0.0))
((0 . "LINE") (100 . "AcDbEntity") (8 . "MASONRY") (62 . 7) (370 . 13) (100 . "AcDbLine") (10 9992.45760181
3288.0846945701 0.0) (11 10143.2890045249 3288.0846945701 0.0))
((0 . "LINE") (100 . "AcDbEntity") (8 . "MASONRY") (62 . 7) (370 . 13) (100 . "AcDbLine") (10 9993.0596719457
2767.7227036199 0.0) (11 9993.0596719457 2718.7799660633 0.0))
((0 . "LINE") (100 . "AcDbEntity") (8 . "MASONRY") (62 . 7) (370 . 13) (100 . "AcDbLine") (10 9993.0596719457
2718.7799660633 0.0) (11 10007.54239819 2718.7799660633 0.0))
((0 . "LINE") (100 . "AcDbEntity") (8 . "MASONRY") (62 . 7) (370 . 13) (100 . "AcDbLine") (10 10018.8546153846
2767.7227036199 0.0) (11 9993.0596719457 2767.7227036199 0.0))
((0 . "LINE") (100 . "AcDbEntity") (8 . "MASONRY") (62 . 7) (370 . 13) (100 . "AcDbLine") (10 9992.45760181
810.7098190045 0.0) (11 9992.45760181 754.1487330317 0.0))
((0 . "LINE") (100 . "AcDbEntity") (8 . "MASONRY") (62 . 7) (370 . 13) (100 . "AcDbLine") (10 9992.45760181
810.7098190045 0.0) (11 10124.4343891403 810.7098190045 0.0))
((0 . "LINE") (100 . "AcDbEntity") (8 . "MASONRY") (62 . 7) (370 . 13) (100 . "AcDbLine") (10 10218.7019457014
52.7912669683 0.0) (11 9992.45760181 52.7912669683 0.0))
((0 . "LINE") (100 . "AcDbEntity") (8 . "MASONRY") (62 . 7) (370 . 13) (100 . "AcDbLine") (10 9998.1150904977
6206.6363800905 0.0) (11 10203.6199095023 6206.6363800905 0.0))
((0 . "LINE") (100 . "AcDbEntity") (8 . "MASONRY") (62 . 7) (370 . 13) (100 . "AcDbLine") (10 9998.1150904977
6206.6363800905 0.0) (11 9998.1150904977 6217.9485972851 0.0))
((0 . "LINE") (100 . "AcDbEntity") (8 . "MASONRY") (62 . 7) (370 . 13) (100 . "AcDbLine") (10 10241.3263800905
4634.2378506787 0.0) (11 9992.45760181 4634.2378506787 0.0))
((0 . "LINE") (100 . "AcDbEntity") (8 . "MASONRY") (62 . 7) (370 . 13) (100 . "AcDbLine") (10 10005.6561085973
6331.0707692308 0.0) (11 10005.6561085973 6391.4027149321 0.0))
((0 . "LINE") (100 . "AcDbEntity") (8 . "MASONRY") (62 . 7) (370 . 13) (100 . "AcDbLine") (10 10005.6561085973
6391.4027149321 0.0) (11 10286.5752488688 6391.4027149321 0.0))
((0 . "LINE") (100 . "AcDbEntity") (8 . "MASONRY") (62 . 7) (370 . 13) (100 . "AcDbLine") (10 10007.54239819
5767.3451696833 0.0) (11 10113.1221719457 5767.3451696833 0.0))
((0 . "LINE") (100 . "AcDbEntity") (8 . "MASONRY") (62 . 7) (370 . 13) (100 . "AcDbLine") (10 10011.3122171946
3981.9004524887 0.0) (11 10105.5797737557 3981.9004524887 0.0))
((0 . "LINE") (100 . "AcDbEntity") (8 . "MASONRY") (62 . 7) (370 . 13) (100 . "AcDbLine") (10 10011.3122171946
1070.8908144796 0.0) (11 10069.7582126697 1070.8908144796 0.0))
((0 . "LINE") (100 . "AcDbEntity") (8 . "MASONRY") (62 . 7) (370 . 13) (100 . "AcDbLine") (10 10011.3122171946
991.7052941176 0.0) (11 10072.2451923077 991.7052941176 0.0))
((0 . "LINE") (100 . "AcDbEntity") (8 . "MASONRY") (62 . 7) (370 . 13) (100 . "AcDbLine") (10 10018.8532352941
5305.4298642534 0.0) (11 10018.8532352941 5316.742081448 0.0))
((0 . "LINE") (100 . "AcDbEntity") (8 . "MASONRY") (62 . 7) (370 . 13) (100 . "AcDbLine") (10 10022.6244343891
3408.7478846154 0.0) (11 10049.0186877828 3408.7478846154 0.0))
((0 . "LINE") (100 . "AcDbEntity") (8 . "MASONRY") (62 . 7) (370 . 13) (100 . "AcDbLine") (10 10026.3942533937
2405.7317533937 0.0) (11 10041.4790497738 2405.7317533937 0.0))
((0 . "LINE") (100 . "AcDbEntity") (8 . "MASONRY") (62 . 7) (370 . 13) (100 . "AcDbLine") (10 10067.8733031674
3682.1266968326 0.0) (11 10033.9366515837 3682.1266968326 0.0))
((0 . "LINE") (100 . "AcDbEntity") (8 . "MASONRY") (62 . 7) (370 . 13) (100 . "AcDbLine") (10 10033.9366515837
2518.8539253394 0.0) (11 10033.9366515837 2488.6877828054 0.0))
((0 . "LINE") (100 . "AcDbEntity") (8 . "MASONRY") (62 . 7) (370 . 13) (100 . "AcDbLine") (10 10033.9366515837
2518.8539253394 0.0) (11 10094.3455769231 2518.8539253394 0.0))
((0 . "LINE") (100 . "AcDbEntity") (8 . "MASONRY") (62 . 7) (370 . 13) (100 . "AcDbLine") (10 10109.3523529412
2269.9851470588 0.0) (11 10033.9366515837 2269.9851470588 0.0))
((0 . "LINE") (100 . "AcDbEntity") (8 . "MASONRY") (62 . 7) (370 . 13) (100 . "AcDbLine") (10 10109.3523529412
2168.1751923077 0.0) (11 10098.0401357466 2168.1751923077 0.0))
((0 . "LINE") (100 . "AcDbEntity") (8 . "MASONRY") (62 . 7) (370 . 13) (100 . "AcDbLine") (10 10098.0401357466
2168.1751923077 0.0) (11 10045.2488687783 2168.1751923077 0.0))
((0 . "LINE") (100 . "AcDbEntity") (8 . "MASONRY") (62 . 7) (370 . 13) (100 . "AcDbLine") (10 10045.2488687783
2168.1751923077 0.0) (11 10033.9366515837 2168.1751923077 0.0))
((0 . "LINE") (100 . "AcDbEntity") (8 . "MASONRY") (62 . 7) (370 . 13) (100 . "AcDbLine") (10 10131.9767873303
5953.9971040724 0.0) (11 10039.592760181 5953.9971040724 0.0))
((0 . "LINE") (100 . "AcDbEntity") (8 . "MASONRY") (62 . 7) (370 . 13) (100 . "AcDbLine") (10 10039.592760181
5953.9971040724 0.0) (11 10039.592760181 5987.9337556561 0.0))
((0 . "LINE") (100 . "AcDbEntity") (8 . "MASONRY") (62 . 7) (370 . 13) (100 . "AcDbLine") (10 10222.4745248869
3633.1073190045 0.0) (11 10037.7064705882 3633.1073190045 0.0))
((0 . "LINE") (100 . "AcDbEntity") (8 . "MASONRY") (62 . 7) (370 . 13) (100 . "AcDbLine") (10 10037.7064705882
2769.6083031674 0.0) (11 10071.6431221719 2769.6083031674 0.0))
((0 . "LINE") (100 . "AcDbEntity") (8 . "MASONRY") (62 . 7) (370 . 13) (100 . "AcDbLine") (10 10252.6385972851
2628.20489819 0.0) (11 10037.7064705882 2628.20489819 0.0))
((0 . "LINE") (100 . "AcDbEntity") (8 . "MASONRY") (62 . 7) (370 . 13) (100 . "AcDbLine") (10 10041.4790497738
4144.0426923077 0.0) (11 10280.920520362 4144.0426923077 0.0))
((0 . "LINE") (100 . "AcDbEntity") (8 . "MASONRY") (62 . 7) (370 . 13) (100 . "AcDbLine") (10 10120.6645701357
3186.274739819 0.0) (11 10041.4790497738 3186.274739819 0.0))
((0 . "LINE") (100 . "AcDbEntity") (8 . "MASONRY") (62 . 7) (370 . 13) (100 . "AcDbLine") (10 10196.0775113122
2720.5882352941 0.0) (11 10041.4790497738 2720.5882352941 0.0))
((0 . "LINE") (100 . "AcDbEntity") (8 . "MASONRY") (62 . 7) (370 . 13) (100 . "AcDbLine") (10 10052.7898868778
6018.0995475113 0.0) (11 10052.7898868778 5999.2459728507 0.0))
((0 . "LINE") (100 . "AcDbEntity") (8 . "MASONRY") (62 . 7) (370 . 13) (100 . "AcDbLine") (10 10148.9437330317
4724.7355882353 0.0) (11 10045.2488687783 4724.7355882353 0.0))
((0 . "LINE") (100 . "AcDbEntity") (8 . "MASONRY") (62 . 7) (370 . 13) (100 . "AcDbLine") (10 10045.2488687783
4249.6224660633 0.0) (11 10139.5164253394 4249.6224660633 0.0))
((0 . "LINE") (100 . "AcDbEntity") (8 . "MASONRY") (62 . 7) (370 . 13) (100 . "AcDbLine") (10 10056.5610859729
5252.6399773756 0.0) (11 10164.0271493213 5252.6399773756 0.0))
((0 . "LINE") (100 . "AcDbEntity") (8 . "MASONRY") (62 . 7) (370 . 13) (100 . "AcDbLine") (10 10060.3309049774
4370.2870361991 0.0) (11 10060.3309049774 4340.0435633484 0.0))
((0 . "LINE") (100 . "AcDbEntity") (8 . "MASONRY") (62 . 7) (370 . 13) (100 . "AcDbLine") (10 10395.92760181
4340.0435633484 0.0) (11 10060.3309049774 4340.0435633484 0.0))
((0 . "LINE") (100 . "AcDbEntity") (8 . "MASONRY") (62 . 7) (370 . 13) (100 . "AcDbLine") (10 10062.2171945701
4317.4957692308 0.0) (11 10062.2171945701 4287.3303167421 0.0))
((0 . "LINE") (100 . "AcDbEntity") (8 . "MASONRY") (62 . 7) (370 . 13) (100 . "AcDbLine") (10 10069.7582126697
1070.8908144796 0.0) (11 10069.7582126697 1059.5785972851 0.0))
((0 . "LINE") (100 . "AcDbEntity") (8 . "MASONRY") (62 . 7) (370 . 13) (100 . "AcDbLine") (10 10263.9508144796
1989.0653167421 0.0) (11 10071.6431221719 1989.0653167421 0.0))
((0 . "LINE") (100 . "AcDbEntity") (8 . "MASONRY") (62 . 7) (370 . 13) (100 . "AcDbLine") (10 10071.6431221719
1268.8532352941 0.0) (11 10101.8099547511 1268.8532352941 0.0))
((0 . "LINE") (100 . "AcDbEntity") (8 . "MASONRY") (62 . 7) (370 . 13) (100 . "AcDbLine") (10 10139.5164253394
1070.8908144796 0.0) (11 10069.7582126697 1070.8908144796 0.0))
((0 . "LINE") (100 . "AcDbEntity") (8 . "MASONRY") (62 . 7) (370 . 13) (100 . "AcDbLine") (10 10086.727918552
991.7052941176 0.0) (11 10072.2451923077 991.7052941176 0.0))
((0 . "LINE") (100 . "AcDbEntity") (8 . "MASONRY") (62 . 7) (370 . 13) (100 . "AcDbLine") (10 10086.727918552
955.8823529412 0.0) (11 10072.2451923077 955.8823529412 0.0))
((0 . "LINE") (100 . "AcDbEntity") (8 . "MASONRY") (62 . 7) (370 . 13) (100 . "AcDbLine") (10 10072.2451923077
955.8823529412 0.0) (11 10072.2451923077 991.7052941176 0.0))
((0 . "LINE") (100 . "AcDbEntity") (8 . "MASONRY") (62 . 7) (370 . 13) (100 . "AcDbLine") (10 10082.9553393665
1440.4214027149 0.0) (11 10343.1363348416 1440.4214027149 0.0))
((0 . "LINE") (100 . "AcDbEntity") (8 . "MASONRY") (62 . 7) (370 . 13) (100 . "AcDbLine") (10 10124.4343891403
177.2256561086 0.0) (11 10082.9553393665 177.2256561086 0.0))
((0 . "LINE") (100 . "AcDbEntity") (8 . "MASONRY") (62 . 7) (370 . 13) (100 . "AcDbLine") (10 10086.727918552
3548.2656900452 0.0) (11 10105.5797737557 3548.2656900452 0.0))
((0 . "LINE") (100 . "AcDbEntity") (8 . "MASONRY") (62 . 7) (370 . 13) (100 . "AcDbLine") (10 10086.727918552
3408.7478846154 0.0) (11 10124.4343891403 3408.7478846154 0.0))
((0 . "LINE") (100 . "AcDbEntity") (8 . "MASONRY") (62 . 7) (370 . 13) (100 . "AcDbLine") (10 10191.3659276018
2405.7317533937 0.0) (11 10086.727918552 2405.7317533937 0.0))
((0 . "LINE") (100 . "AcDbEntity") (8 . "MASONRY") (62 . 7) (370 . 13) (100 . "AcDbLine") (10 10150.8286425339
2518.8539253394 0.0) (11 10094.3455769231 2518.8539253394 0.0))
((0 . "LINE") (100 . "AcDbEntity") (8 . "MASONRY") (62 . 7) (370 . 13) (100 . "AcDbLine") (10 10094.3455769231
2518.8539253394 0.0) (11 10094.3455769231 2563.5007239819 0.0))
((0 . "LINE") (100 . "AcDbEntity") (8 . "MASONRY") (62 . 7) (370 . 13) (100 . "AcDbLine") (10 10094.3455769231
2563.5007239819 0.0) (11 10150.8286425339 2563.5007239819 0.0))
((0 . "LINE") (100 . "AcDbEntity") (8 . "MASONRY") (62 . 7) (370 . 13) (100 . "AcDbLine") (10 10094.2675565611
1523.3795022624 0.0) (11 10335.5966968326 1523.3795022624 0.0))
((0 . "LINE") (100 . "AcDbEntity") (8 . "MASONRY") (62 . 7) (370 . 13) (100 . "AcDbLine") (10 10335.5966968326
1523.3795022624 0.0) (11 10388.3852036199 1523.3795022624 0.0))
((0 . "LINE") (100 . "AcDbEntity") (8 . "MASONRY") (62 . 7) (370 . 13) (100 . "AcDbLine") (10 10098.0401357466
354.4485520362 0.0) (11 10131.9767873303 354.4485520362 0.0))
((0 . "LINE") (100 . "AcDbEntity") (8 . "MASONRY") (62 . 7) (370 . 13) (100 . "AcDbLine") (10 10098.0401357466
354.4485520362 0.0) (11 10098.0401357466 418.5520361991 0.0))
((0 . "LINE") (100 . "AcDbEntity") (8 . "MASONRY") (62 . 7) (370 . 13) (100 . "AcDbLine") (10 10101.8099547511
3046.7569343891 0.0) (11 10101.8099547511 3058.0691515837 0.0))
((0 . "LINE") (100 . "AcDbEntity") (8 . "MASONRY") (62 . 7) (370 . 13) (100 . "AcDbLine") (10 10098.0401357466
429.8642533937 0.0) (11 10098.0401357466 418.5520361991 0.0))
((0 . "LINE") (100 . "AcDbEntity") (8 . "MASONRY") (62 . 7) (370 . 13) (100 . "AcDbLine") (10 10101.8099547511
6025.6409049774 0.0) (11 10194.19260181 6025.6409049774 0.0))
((0 . "LINE") (100 . "AcDbEntity") (8 . "MASONRY") (62 . 7) (370 . 13) (100 . "AcDbLine") (10 10103.6948642534
5889.8942986425 0.0) (11 10103.6948642534 5897.4360180995 0.0))
((0 . "LINE") (100 . "AcDbEntity") (8 . "MASONRY") (62 . 7) (370 . 13) (100 . "AcDbLine") (10 10109.3509728507
5546.7576244344 0.0) (11 10237.556561086 5546.7576244344 0.0))
((0 . "LINE") (100 . "AcDbEntity") (8 . "MASONRY") (62 . 7) (370 . 13) (100 . "AcDbLine") (10 10109.3509728507
5546.7576244344 0.0) (11 10109.3509728507 5602.1912217195 0.0))
((0 . "LINE") (100 . "AcDbEntity") (8 . "MASONRY") (62 . 7) (370 . 13) (100 . "AcDbLine") (10 10109.3509728507
5602.1912217195 0.0) (11 10237.556561086 5602.1912217195 0.0))
((0 . "LINE") (100 . "AcDbEntity") (8 . "MASONRY") (62 . 7) (370 . 13) (100 . "AcDbLine") (10 10105.5797737557
2944.946979638 0.0) (11 10238.8394004525 2944.946979638 0.0))
((0 . "LINE") (100 . "AcDbEntity") (8 . "MASONRY") (62 . 7) (370 . 13) (100 . "AcDbLine") (10 10105.5797737557
3007.1648642534 0.0) (11 10105.5797737557 2944.946979638 0.0))
((0 . "LINE") (100 . "AcDbEntity") (8 . "MASONRY") (62 . 7) (370 . 13) (100 . "AcDbLine") (10 10211.1623076923
418.5520361991 0.0) (11 10098.0401357466 418.5520361991 0.0))
((0 . "LINE") (100 . "AcDbEntity") (8 . "MASONRY") (62 . 7) (370 . 13) (100 . "AcDbLine") (10 10105.5797737557
5833.3332126697 0.0) (11 10105.5797737557 5855.9576470588 0.0))
((0 . "LINE") (100 . "AcDbEntity") (8 . "MASONRY") (62 . 7) (370 . 13) (100 . "AcDbLine") (10 10105.5797737557
5833.3332126697 0.0) (11 10124.4343891403 5833.3332126697 0.0))
((0 . "LINE") (100 . "AcDbEntity") (8 . "MASONRY") (62 . 7) (370 . 13) (100 . "AcDbLine") (10 10107.4336085973
5629.7133031674 0.0) (11 10107.4336085973 5643.6626696833 0.0))
((0 . "LINE") (100 . "AcDbEntity") (8 . "MASONRY") (62 . 7) (370 . 13) (100 . "AcDbLine") (10 10107.4336085973
5643.6626696833 0.0) (11 10164.5546493213 5643.6626696833 0.0))
((0 . "LINE") (100 . "AcDbEntity") (8 . "MASONRY") (62 . 7) (370 . 13) (100 . "AcDbLine") (10 10173.4530769231
3472.850678733 0.0) (11 10111.2358823529 3472.850678733 0.0))
((0 . "LINE") (100 . "AcDbEntity") (8 . "MASONRY") (62 . 7) (370 . 13) (100 . "AcDbLine") (10 10241.3263800905
3506.6326696833 0.0) (11 10111.2358823529 3506.6326696833 0.0))
((0 . "LINE") (100 . "AcDbEntity") (8 . "MASONRY") (62 . 7) (370 . 13) (100 . "AcDbLine") (10 10111.2358823529
3506.6326696833 0.0) (11 10111.2358823529 3472.850678733 0.0))
((0 . "LINE") (100 . "AcDbEntity") (8 . "MASONRY") (62 . 7) (370 . 13) (100 . "AcDbLine") (10 10105.5797737557
3007.1648642534 0.0) (11 10105.5797737557 3020.3619909502 0.0))
((0 . "LINE") (100 . "AcDbEntity") (8 . "MASONRY") (62 . 7) (370 . 13) (100 . "AcDbLine") (10 10105.5797737557
2771.4932126697 0.0) (11 10245.0975791855 2771.4932126697 0.0))
((0 . "LINE") (100 . "AcDbEntity") (8 . "MASONRY") (62 . 7) (370 . 13) (100 . "AcDbLine") (10 10105.5797737557
3007.1648642534 0.0) (11 10124.4343891403 3007.1648642534 0.0))
((0 . "LINE") (100 . "AcDbEntity") (8 . "MASONRY") (62 . 7) (370 . 13) (100 . "AcDbLine") (10 10109.3523529412
2168.1751923077 0.0) (11 10282.8012895928 2168.1751923077 0.0))
((0 . "LINE") (100 . "AcDbEntity") (8 . "MASONRY") (62 . 7) (370 . 13) (100 . "AcDbLine") (10 10282.8012895928
2168.1751923077 0.0) (11 10282.8012895928 2194.5701357466 0.0))
((0 . "LINE") (100 . "AcDbEntity") (8 . "MASONRY") (62 . 7) (370 . 13) (100 . "AcDbLine") (10 10109.3523529412
991.7052941176 0.0) (11 10143.2890045249 991.7052941176 0.0))
((0 . "LINE") (100 . "AcDbEntity") (8 . "MASONRY") (62 . 7) (370 . 13) (100 . "AcDbLine") (10 10113.1221719457
5441.1764705882 0.0) (11 10192.3076923077 5441.1764705882 0.0))
((0 . "LINE") (100 . "AcDbEntity") (8 . "MASONRY") (62 . 7) (370 . 13) (100 . "AcDbLine") (10 10118.778280543
4517.3458597285 0.0) (11 10118.778280543 4477.829739819 0.0))
((0 . "LINE") (100 . "AcDbEntity") (8 . "MASONRY") (62 . 7) (370 . 13) (100 . "AcDbLine") (10 10118.778280543
4477.829739819 0.0) (11 10312.9722624434 4477.829739819 0.0))
((0 . "LINE") (100 . "AcDbEntity") (8 . "MASONRY") (62 . 7) (370 . 13) (100 . "AcDbLine") (10 10118.778280543
4517.3458597285 0.0) (11 10339.3665158371 4517.3458597285 0.0))
((0 . "LINE") (100 . "AcDbEntity") (8 . "MASONRY") (62 . 7) (370 . 13) (100 . "AcDbLine") (10 10124.4343891403
1342.3840271493 0.0) (11 10150.9839932127 1342.3840271493 0.0))
((0 . "LINE") (100 . "AcDbEntity") (8 . "MASONRY") (62 . 7) (370 . 13) (100 . "AcDbLine") (10 10128.2042081448
4924.585678733 0.0) (11 10128.2042081448 4892.5339366516 0.0))
((0 . "LINE") (100 . "AcDbEntity") (8 . "MASONRY") (62 . 7) (370 . 13) (100 . "AcDbLine") (10 10243.2126696833
4892.5339366516 0.0) (11 10128.2042081448 4892.5339366516 0.0))
((0 . "LINE") (100 . "AcDbEntity") (8 . "MASONRY") (62 . 7) (370 . 13) (100 . "AcDbLine") (10 10191.3659276018
2269.9851470588 0.0) (11 10128.2042081448 2269.9851470588 0.0))
((0 . "LINE") (100 . "AcDbEntity") (8 . "MASONRY") (62 . 7) (370 . 13) (100 . "AcDbLine") (10 10128.2042081448
1689.2901809955 0.0) (11 10128.2042081448 1676.0930542986 0.0))
((0 . "LINE") (100 . "AcDbEntity") (8 . "MASONRY") (62 . 7) (370 . 13) (100 . "AcDbLine") (10 10128.2042081448
1676.0930542986 0.0) (11 10180.9954751131 1676.0930542986 0.0))
((0 . "LINE") (100 . "AcDbEntity") (8 . "MASONRY") (62 . 7) (370 . 13) (100 . "AcDbLine") (10 10131.9767873303
3989.4414705882 0.0) (11 10318.7788914027 3989.4414705882 0.0))
((0 . "LINE") (100 . "AcDbEntity") (8 . "MASONRY") (62 . 7) (370 . 13) (100 . "AcDbLine") (10 10131.9767873303
1730.7692307692 0.0) (11 10197.963800905 1730.7692307692 0.0))
((0 . "LINE") (100 . "AcDbEntity") (8 . "MASONRY") (62 . 7) (370 . 13) (100 . "AcDbLine") (10 10131.9767873303
248.8687782805 0.0) (11 10131.9767873303 260.1809954751 0.0))
((0 . "LINE") (100 . "AcDbEntity") (8 . "MASONRY") (62 . 7) (370 . 13) (100 . "AcDbLine") (10 10131.9767873303
260.1809954751 0.0) (11 10131.9767873303 354.4485520362 0.0))
((0 . "LINE") (100 . "AcDbEntity") (8 . "MASONRY") (62 . 7) (370 . 13) (100 . "AcDbLine") (10 10131.9767873303
354.4485520362 0.0) (11 10354.4485520362 354.4485520362 0.0))
((0 . "LINE") (100 . "AcDbEntity") (8 . "MASONRY") (62 . 7) (370 . 13) (100 . "AcDbLine") (10 10139.5164253394
4211.9159954751 0.0) (11 10139.5164253394 4249.6224660633 0.0))
((0 . "LINE") (100 . "AcDbEntity") (8 . "MASONRY") (62 . 7) (370 . 13) (100 . "AcDbLine") (10 10165.913438914
4249.6224660633 0.0) (11 10139.5164253394 4249.6224660633 0.0))
((0 . "LINE") (100 . "AcDbEntity") (8 . "MASONRY") (62 . 7) (370 . 13) (100 . "AcDbLine") (10 10139.5164253394
4211.9159954751 0.0) (11 10279.0342307692 4211.9159954751 0.0))
((0 . "LINE") (100 . "AcDbEntity") (8 . "MASONRY") (62 . 7) (370 . 13) (100 . "AcDbLine") (10 10279.0342307692
4211.9159954751 0.0) (11 10279.0342307692 4230.7692307692 0.0))
((0 . "LINE") (100 . "AcDbEntity") (8 . "MASONRY") (62 . 7) (370 . 13) (100 . "AcDbLine") (10 10143.2876244344
3925.3393665158 0.0) (11 10143.2876244344 3951.735 0.0))
((0 . "LINE") (100 . "AcDbEntity") (8 . "MASONRY") (62 . 7) (370 . 13) (100 . "AcDbLine") (10 10143.2876244344
3863.1221719457 0.0) (11 10143.2876244344 3883.8616968326 0.0))
((0 . "LINE") (100 . "AcDbEntity") (8 . "MASONRY") (62 . 7) (370 . 13) (100 . "AcDbLine") (10 10167.7983484163
3186.274739819 0.0) (11 10143.2890045249 3186.274739819 0.0))
((0 . "LINE") (100 . "AcDbEntity") (8 . "MASONRY") (62 . 7) (370 . 13) (100 . "AcDbLine") (10 10148.9437330317
4724.7355882353 0.0) (11 10148.9437330317 4785.0678733032 0.0))
((0 . "LINE") (100 . "AcDbEntity") (8 . "MASONRY") (62 . 7) (370 . 13) (100 . "AcDbLine") (10 10148.9437330317
4796.3800904977 0.0) (11 10148.9437330317 4785.0678733032 0.0))
((0 . "LINE") (100 . "AcDbEntity") (8 . "MASONRY") (62 . 7) (370 . 13) (100 . "AcDbLine") (10 10388.3852036199
4724.7355882353 0.0) (11 10148.9437330317 4724.7355882353 0.0))
((0 . "LINE") (100 . "AcDbEntity") (8 . "MASONRY") (62 . 7) (370 . 13) (100 . "AcDbLine") (10 10143.2876244344
3863.1221719457 0.0) (11 10196.0775113122 3863.1221719457 0.0))
((0 . "LINE") (100 . "AcDbEntity") (8 . "MASONRY") (62 . 7) (370 . 13) (100 . "AcDbLine") (10 10173.4510067873
131.9767873303 0.0) (11 10173.4510067873 119.4549095023 0.0))
((0 . "LINE") (100 . "AcDbEntity") (8 . "MASONRY") (62 . 7) (370 . 13) (100 . "AcDbLine") (10 10173.4510067873
119.4549095023 0.0) (11 10147.0588235294 119.4549095023 0.0))
((0 . "LINE") (100 . "AcDbEntity") (8 . "MASONRY") (62 . 7) (370 . 13) (100 . "AcDbLine") (10 10177.2256561086
5211.1609276018 0.0) (11 10150.8286425339 5211.1609276018 0.0))
((0 . "LINE") (100 . "AcDbEntity") (8 . "MASONRY") (62 . 7) (370 . 13) (100 . "AcDbLine") (10 10154.599841629
4841.628959276 0.0) (11 10154.599841629 4856.7123755656 0.0))
((0 . "LINE") (100 . "AcDbEntity") (8 . "MASONRY") (62 . 7) (370 . 13) (100 . "AcDbLine") (10 10148.9437330317
4796.3800904977 0.0) (11 10148.9437330317 4819.0045248869 0.0))
((0 . "LINE") (100 . "AcDbEntity") (8 . "MASONRY") (62 . 7) (370 . 13) (100 . "AcDbLine") (10 10248.875678733
3061.8403506787 0.0) (11 10150.8286425339 3061.8403506787 0.0))
((0 . "LINE") (100 . "AcDbEntity") (8 . "MASONRY") (62 . 7) (370 . 13) (100 . "AcDbLine") (10 10150.8286425339
2518.8539253394 0.0) (11 10150.8286425339 2563.5007239819 0.0))
((0 . "LINE") (100 . "AcDbEntity") (8 . "MASONRY") (62 . 7) (370 . 13) (100 . "AcDbLine") (10 10150.8286425339
2575.4150113122 0.0) (11 10150.8286425339 2563.5007239819 0.0))
((0 . "LINE") (100 . "AcDbEntity") (8 . "MASONRY") (62 . 7) (370 . 13) (100 . "AcDbLine") (10 10150.8286425339
2518.8539253394 0.0) (11 10191.3659276018 2518.8539253394 0.0))
((0 . "LINE") (100 . "AcDbEntity") (8 . "MASONRY") (62 . 7) (370 . 13) (100 . "AcDbLine") (10 10392.1577828054
1263.3517873303 0.0) (11 10339.3665158371 1263.3517873303 0.0))
((0 . "LINE") (100 . "AcDbEntity") (8 . "MASONRY") (62 . 7) (370 . 13) (100 . "AcDbLine") (10 10339.3665158371
1263.3517873303 0.0) (11 10150.9839932127 1263.3517873303 0.0))
((0 . "LINE") (100 . "AcDbEntity") (8 . "MASONRY") (62 . 7) (370 . 13) (100 . "AcDbLine") (10 10150.9839932127
1263.3517873303 0.0) (11 10150.9839932127 1274.5107239819 0.0))
((0 . "LINE") (100 . "AcDbEntity") (8 . "MASONRY") (62 . 7) (370 . 13) (100 . "AcDbLine") (10 10150.9839932127
1274.5107239819 0.0) (11 10150.9839932127 1342.3840271493 0.0))
((0 . "LINE") (100 . "AcDbEntity") (8 . "MASONRY") (62 . 7) (370 . 13) (100 . "AcDbLine") (10 10165.913438914
1342.3840271493 0.0) (11 10150.9839932127 1342.3840271493 0.0))
((0 . "LINE") (100 . "AcDbEntity") (8 . "MASONRY") (62 . 7) (370 . 13) (100 . "AcDbLine") (10 10152.7149321267
1185.2958257919 0.0) (11 10152.7149321267 1233.0316742081 0.0))
((0 . "LINE") (100 . "AcDbEntity") (8 . "MASONRY") (62 . 7) (370 . 13) (100 . "AcDbLine") (10 10316.742081448
177.2256561086 0.0) (11 10150.8286425339 177.2256561086 0.0))
((0 . "LINE") (100 . "AcDbEntity") (8 . "MASONRY") (62 . 7) (370 . 13) (100 . "AcDbLine") (10 10148.9437330317
4796.3800904977 0.0) (11 10162.1408597285 4796.3800904977 0.0))
((0 . "LINE") (100 . "AcDbEntity") (8 . "MASONRY") (62 . 7) (370 . 13) (100 . "AcDbLine") (10 10152.7149321267
1185.2958257919 0.0) (11 10290.34989819 1185.2958257919 0.0))
((0 . "LINE") (100 . "AcDbEntity") (8 . "MASONRY") (62 . 7) (370 . 13) (100 . "AcDbLine") (10 10158.371040724
5946.4553846154 0.0) (11 10250.7550678733 5946.4553846154 0.0))
((0 . "LINE") (100 . "AcDbEntity") (8 . "MASONRY") (62 . 7) (370 . 13) (100 . "AcDbLine") (10 10388.3852036199 5846.0025
0.0) (11 10166.9622171946 5846.0025 0.0))
((0 . "LINE") (100 . "AcDbEntity") (8 . "MASONRY") (62 . 7) (370 . 13) (100 . "AcDbLine") (10 10166.9622171946 5846.0025
0.0) (11 10166.9622171946 5822.0209954751 0.0))
((0 . "LINE") (100 . "AcDbEntity") (8 . "MASONRY") (62 . 7) (370 . 13) (100 . "AcDbLine") (10 10166.9622171946
5822.0209954751 0.0) (11 10166.9622171946 5765.4599095023 0.0))
((0 . "LINE") (100 . "AcDbEntity") (8 . "MASONRY") (62 . 7) (370 . 13) (100 . "AcDbLine") (10 10158.371040724
4402.3380882353 0.0) (11 10246.9838687783 4402.3380882353 0.0))
((0 . "LINE") (100 . "AcDbEntity") (8 . "MASONRY") (62 . 7) (370 . 13) (100 . "AcDbLine") (10 10158.371040724
3009.0497737557 0.0) (11 10196.0775113122 3009.0497737557 0.0))
((0 . "LINE") (100 . "AcDbEntity") (8 . "MASONRY") (62 . 7) (370 . 13) (100 . "AcDbLine") (10 10164.5546493213
5643.6626696833 0.0) (11 10207.3897285068 5643.6626696833 0.0))
((0 . "LINE") (100 . "AcDbEntity") (8 . "MASONRY") (62 . 7) (370 . 13) (100 . "AcDbLine") (10 10345.0226244344
5727.752760181 0.0) (11 10164.5546493213 5727.752760181 0.0))
((0 . "LINE") (100 . "AcDbEntity") (8 . "MASONRY") (62 . 7) (370 . 13) (100 . "AcDbLine") (10 10164.5546493213
5727.752760181 0.0) (11 10164.5546493213 5643.6626696833 0.0))
((0 . "LINE") (100 . "AcDbEntity") (8 . "MASONRY") (62 . 7) (370 . 13) (100 . "AcDbLine") (10 10162.1408597285
5335.5960067873 0.0) (11 10184.7652941176 5335.5960067873 0.0))
((0 . "LINE") (100 . "AcDbEntity") (8 . "MASONRY") (62 . 7) (370 . 13) (100 . "AcDbLine") (10 10164.0271493213
5305.4298642534 0.0) (11 10164.0271493213 5252.6399773756 0.0))
((0 . "LINE") (100 . "AcDbEntity") (8 . "MASONRY") (62 . 7) (370 . 13) (100 . "AcDbLine") (10 10162.1408597285
3406.8622850679 0.0) (11 10173.4530769231 3406.8622850679 0.0))
((0 . "LINE") (100 . "AcDbEntity") (8 . "MASONRY") (62 . 7) (370 . 13) (100 . "AcDbLine") (10 10162.1408597285
3276.927138009 0.0) (11 10177.2256561086 3276.927138009 0.0))
((0 . "LINE") (100 . "AcDbEntity") (8 . "MASONRY") (62 . 7) (370 . 13) (100 . "AcDbLine") (10 10177.2256561086
3276.927138009 0.0) (11 10312.9722624434 3276.927138009 0.0))
((0 . "LINE") (100 . "AcDbEntity") (8 . "MASONRY") (62 . 7) (370 . 13) (100 . "AcDbLine") (10 10196.0775113122
2865.761459276 0.0) (11 10162.1408597285 2865.761459276 0.0))
((0 . "LINE") (100 . "AcDbEntity") (8 . "MASONRY") (62 . 7) (370 . 13) (100 . "AcDbLine") (10 10162.1408597285
986.0478054299 0.0) (11 10184.7652941176 986.0478054299 0.0))
((0 . "LINE") (100 . "AcDbEntity") (8 . "MASONRY") (62 . 7) (370 . 13) (100 . "AcDbLine") (10 10162.1408597285
889.8953393665 0.0) (11 10162.1408597285 923.8319909502 0.0))
((0 . "LINE") (100 . "AcDbEntity") (8 . "MASONRY") (62 . 7) (370 . 13) (100 . "AcDbLine") (10 10211.1623076923
855.9573076923 0.0) (11 10162.1408597285 855.9573076923 0.0))
((0 . "LINE") (100 . "AcDbEntity") (8 . "MASONRY") (62 . 7) (370 . 13) (100 . "AcDbLine") (10 10164.0271493213
690.0452488688 0.0) (11 10164.0271493213 618.4021266968 0.0))
((0 . "LINE") (100 . "AcDbEntity") (8 . "MASONRY") (62 . 7) (370 . 13) (100 . "AcDbLine") (10 10388.3852036199
5252.6399773756 0.0) (11 10164.0271493213 5252.6399773756 0.0))
((0 . "LINE") (100 . "AcDbEntity") (8 . "MASONRY") (62 . 7) (370 . 13) (100 . "AcDbLine") (10 10167.7983484163
3186.274739819 0.0) (11 10167.7983484163 3197.5869570136 0.0))
((0 . "LINE") (100 . "AcDbEntity") (8 . "MASONRY") (62 . 7) (370 . 13) (100 . "AcDbLine") (10 10165.913438914
948.3413348416 0.0) (11 10222.4745248869 948.3413348416 0.0))
((0 . "LINE") (100 . "AcDbEntity") (8 . "MASONRY") (62 . 7) (370 . 13) (100 . "AcDbLine") (10 10165.913438914
565.6108597285 0.0) (11 10165.913438914 537.3303167421 0.0))
((0 . "LINE") (100 . "AcDbEntity") (8 . "MASONRY") (62 . 7) (370 . 13) (100 . "AcDbLine") (10 10165.913438914
537.3303167421 0.0) (11 10324.284479638 537.3303167421 0.0))
((0 . "LINE") (100 . "AcDbEntity") (8 . "MASONRY") (62 . 7) (370 . 13) (100 . "AcDbLine") (10 10173.4530769231
3363.4990158371 0.0) (11 10173.4530769231 3406.8622850679 0.0))
((0 . "LINE") (100 . "AcDbEntity") (8 . "MASONRY") (62 . 7) (370 . 13) (100 . "AcDbLine") (10 10173.4530769231
3472.850678733 0.0) (11 10173.4530769231 3406.8622850679 0.0))
((0 . "LINE") (100 . "AcDbEntity") (8 . "MASONRY") (62 . 7) (370 . 13) (100 . "AcDbLine") (10 10167.7983484163
3186.274739819 0.0) (11 10250.7536877828 3186.274739819 0.0))
((0 . "LINE") (100 . "AcDbEntity") (8 . "MASONRY") (62 . 7) (370 . 13) (100 . "AcDbLine") (10 10184.7652941176
986.0478054299 0.0) (11 10184.7652941176 976.6204977376 0.0))
((0 . "LINE") (100 . "AcDbEntity") (8 . "MASONRY") (62 . 7) (370 . 13) (100 . "AcDbLine") (10 10184.7652941176
1004.9024208145 0.0) (11 10184.7652941176 986.0478054299 0.0))
((0 . "LINE") (100 . "AcDbEntity") (8 . "MASONRY") (62 . 7) (370 . 13) (100 . "AcDbLine") (10 10173.4530769231
3472.850678733 0.0) (11 10241.3263800905 3472.850678733 0.0))
((0 . "LINE") (100 . "AcDbEntity") (8 . "MASONRY") (62 . 7) (370 . 13) (100 . "AcDbLine") (10 10173.4530769231
1864.6309276018 0.0) (11 10199.8500904977 1864.6309276018 0.0))
((0 . "LINE") (100 . "AcDbEntity") (8 . "MASONRY") (62 . 7) (370 . 13) (100 . "AcDbLine") (10 10173.4530769231
1632.7290950226 0.0) (11 10173.4530769231 1640.2714932127 0.0))
((0 . "LINE") (100 . "AcDbEntity") (8 . "MASONRY") (62 . 7) (370 . 13) (100 . "AcDbLine") (10 10173.4530769231
1595.0226244344 0.0) (11 10348.7924434389 1595.0226244344 0.0))
((0 . "LINE") (100 . "AcDbEntity") (8 . "MASONRY") (62 . 7) (370 . 13) (100 . "AcDbLine") (10 10207.3897285068
5015.0834162896 0.0) (11 10184.7652941176 5015.0834162896 0.0))
((0 . "LINE") (100 . "AcDbEntity") (8 . "MASONRY") (62 . 7) (370 . 13) (100 . "AcDbLine") (10 10196.0775113122
3672.6993891403 0.0) (11 10184.7652941176 3672.6993891403 0.0))
((0 . "LINE") (100 . "AcDbEntity") (8 . "MASONRY") (62 . 7) (370 . 13) (100 . "AcDbLine") (10 10184.7652941176
1004.9024208145 0.0) (11 10199.8500904977 1004.9024208145 0.0))
((0 . "LINE") (100 . "AcDbEntity") (8 . "MASONRY") (62 . 7) (370 . 13) (100 . "AcDbLine") (10 10184.7652941176
1085.9728506787 0.0) (11 10184.7652941176 1074.6544230769 0.0))
((0 . "LINE") (100 . "AcDbEntity") (8 . "MASONRY") (62 . 7) (370 . 13) (100 . "AcDbLine") (10 10184.7652941176
1074.6544230769 0.0) (11 10184.7652941176 1004.9024208145 0.0))
((0 . "LINE") (100 . "AcDbEntity") (8 . "MASONRY") (62 . 7) (370 . 13) (100 . "AcDbLine") (10 10282.8054298643
248.8687782805 0.0) (11 10184.7652941176 248.8687782805 0.0))
((0 . "LINE") (100 . "AcDbEntity") (8 . "MASONRY") (62 . 7) (370 . 13) (100 . "AcDbLine") (10 10191.3659276018
2405.7317533937 0.0) (11 10388.3852036199 2405.7317533937 0.0))
((0 . "LINE") (100 . "AcDbEntity") (8 . "MASONRY") (62 . 7) (370 . 13) (100 . "AcDbLine") (10 10191.3659276018
2405.7317533937 0.0) (11 10191.3659276018 2334.0872511312 0.0))
((0 . "LINE") (100 . "AcDbEntity") (8 . "MASONRY") (62 . 7) (370 . 13) (100 . "AcDbLine") (10 10191.3659276018
2518.8539253394 0.0) (11 10191.3659276018 2405.7317533937 0.0))
((0 . "LINE") (100 . "AcDbEntity") (8 . "MASONRY") (62 . 7) (370 . 13) (100 . "AcDbLine") (10 10196.0775113122
5394.0420022624 0.0) (11 10188.5378733032 5394.0420022624 0.0))
((0 . "LINE") (100 . "AcDbEntity") (8 . "MASONRY") (62 . 7) (370 . 13) (100 . "AcDbLine") (10 10191.3659276018
2518.8539253394 0.0) (11 10363.8758597285 2518.8539253394 0.0))
((0 . "LINE") (100 . "AcDbEntity") (8 . "MASONRY") (62 . 7) (370 . 13) (100 . "AcDbLine") (10 10194.19260181
6025.6409049774 0.0) (11 10207.3897285068 6025.6409049774 0.0))
((0 . "LINE") (100 . "AcDbEntity") (8 . "MASONRY") (62 . 7) (370 . 13) (100 . "AcDbLine") (10 10194.19260181
6093.6754298643 0.0) (11 10194.19260181 6025.6409049774 0.0))
((0 . "LINE") (100 . "AcDbEntity") (8 . "MASONRY") (62 . 7) (370 . 13) (100 . "AcDbLine") (10 10192.3076923077
5493.9663574661 0.0) (11 10192.3076923077 5441.1764705882 0.0))
((0 . "LINE") (100 . "AcDbEntity") (8 . "MASONRY") (62 . 7) (370 . 13) (100 . "AcDbLine") (10 10388.3852036199
5441.1764705882 0.0) (11 10192.3076923077 5441.1764705882 0.0))
((0 . "LINE") (100 . "AcDbEntity") (8 . "MASONRY") (62 . 7) (370 . 13) (100 . "AcDbLine") (10 10192.3076923077
4251.5080656109 0.0) (11 10230.0141628959 4251.5080656109 0.0))
((0 . "LINE") (100 . "AcDbEntity") (8 . "MASONRY") (62 . 7) (370 . 13) (100 . "AcDbLine") (10 10377.0729864253
1342.3840271493 0.0) (11 10192.3076923077 1342.3840271493 0.0))
((0 . "LINE") (100 . "AcDbEntity") (8 . "MASONRY") (62 . 7) (370 . 13) (100 . "AcDbLine") (10 10191.3659276018
2334.0872511312 0.0) (11 10191.3659276018 2269.9851470588 0.0))
((0 . "LINE") (100 . "AcDbEntity") (8 . "MASONRY") (62 . 7) (370 . 13) (100 . "AcDbLine") (10 10392.1577828054
2334.0872511312 0.0) (11 10191.3659276018 2334.0872511312 0.0))
((0 . "LINE") (100 . "AcDbEntity") (8 . "MASONRY") (62 . 7) (370 . 13) (100 . "AcDbLine") (10 10373.3031674208
6093.6754298643 0.0) (11 10194.19260181 6093.6754298643 0.0))
((0 . "LINE") (100 . "AcDbEntity") (8 . "MASONRY") (62 . 7) (370 . 13) (100 . "AcDbLine") (10 10196.0775113122
3863.1221719457 0.0) (11 10211.1623076923 3863.1221719457 0.0))
((0 . "LINE") (100 . "AcDbEntity") (8 . "MASONRY") (62 . 7) (370 . 13) (100 . "AcDbLine") (10 10211.1623076923
3863.1221719457 0.0) (11 10226.2443438914 3863.1221719457 0.0))
((0 . "LINE") (100 . "AcDbEntity") (8 . "MASONRY") (62 . 7) (370 . 13) (100 . "AcDbLine") (10 10226.2443438914
3863.1221719457 0.0) (11 10263.9508144796 3863.1221719457 0.0))
((0 . "LINE") (100 . "AcDbEntity") (8 . "MASONRY") (62 . 7) (370 . 13) (100 . "AcDbLine") (10 10288.4615384615
2269.9851470588 0.0) (11 10191.3659276018 2269.9851470588 0.0))
((0 . "LINE") (100 . "AcDbEntity") (8 . "MASONRY") (62 . 7) (370 . 13) (100 . "AcDbLine") (10 10196.0775113122
1806.029581448 0.0) (11 10211.1623076923 1806.029581448 0.0))
((0 . "LINE") (100 . "AcDbEntity") (8 . "MASONRY") (62 . 7) (370 . 13) (100 . "AcDbLine") (10 10211.1623076923
1806.029581448 0.0) (11 10395.92760181 1806.029581448 0.0))
((0 . "LINE") (100 . "AcDbEntity") (8 . "MASONRY") (62 . 7) (370 . 13) (100 . "AcDbLine") (10 10197.963800905
1760.9360633484 0.0) (11 10197.963800905 1730.7692307692 0.0))
((0 . "LINE") (100 . "AcDbEntity") (8 . "MASONRY") (62 . 7) (370 . 13) (100 . "AcDbLine") (10 10199.8500904977
2096.5313800905 0.0) (11 10226.2443438914 2096.5313800905 0.0))
((0 . "LINE") (100 . "AcDbEntity") (8 . "MASONRY") (62 . 7) (370 . 13) (100 . "AcDbLine") (10 10199.8500904977
1855.2036199095 0.0) (11 10199.8500904977 1864.6309276018 0.0))
((0 . "LINE") (100 . "AcDbEntity") (8 . "MASONRY") (62 . 7) (370 . 13) (100 . "AcDbLine") (10 10309.1996832579
1864.6309276018 0.0) (11 10199.8500904977 1864.6309276018 0.0))
((0 . "LINE") (100 . "AcDbEntity") (8 . "MASONRY") (62 . 7) (370 . 13) (100 . "AcDbLine") (10 10197.963800905
1730.7692307692 0.0) (11 10230.0141628959 1730.7692307692 0.0))
((0 . "LINE") (100 . "AcDbEntity") (8 . "MASONRY") (62 . 7) (370 . 13) (100 . "AcDbLine") (10 10267.7233936652
6206.6363800905 0.0) (11 10203.6199095023 6206.6363800905 0.0))
((0 . "LINE") (100 . "AcDbEntity") (8 . "MASONRY") (62 . 7) (370 . 13) (100 . "AcDbLine") (10 10203.6199095023
6157.6170135747 0.0) (11 10203.6199095023 6206.6363800905 0.0))
((0 . "LINE") (100 . "AcDbEntity") (8 . "MASONRY") (62 . 7) (370 . 13) (100 . "AcDbLine") (10 10230.0141628959
3710.407239819 0.0) (11 10211.1623076923 3710.407239819 0.0))
((0 . "LINE") (100 . "AcDbEntity") (8 . "MASONRY") (62 . 7) (370 . 13) (100 . "AcDbLine") (10 10214.9321266968
2130.467341629 0.0) (11 10214.9321266968 2119.1551244344 0.0))
((0 . "LINE") (100 . "AcDbEntity") (8 . "MASONRY") (62 . 7) (370 . 13) (100 . "AcDbLine") (10 10218.7019457014
3333.3335633484 0.0) (11 10305.4298642534 3333.3335633484 0.0))
((0 . "LINE") (100 . "AcDbEntity") (8 . "MASONRY") (62 . 7) (370 . 13) (100 . "AcDbLine") (10 10305.4298642534
3333.3335633484 0.0) (11 10343.1363348416 3333.3335633484 0.0))
((0 . "LINE") (100 . "AcDbEntity") (8 . "MASONRY") (62 . 7) (370 . 13) (100 . "AcDbLine") (10 10218.7019457014
2865.761459276 0.0) (11 10326.1652488688 2865.761459276 0.0))
((0 . "LINE") (100 . "AcDbEntity") (8 . "MASONRY") (62 . 7) (370 . 13) (100 . "AcDbLine") (10 10326.1652488688
2865.761459276 0.0) (11 10326.1652488688 2880.8448755656 0.0))
((0 . "LINE") (100 . "AcDbEntity") (8 . "MASONRY") (62 . 7) (370 . 13) (100 . "AcDbLine") (10 10339.3665158371
1674.2081447964 0.0) (11 10218.7019457014 1674.2081447964 0.0))
((0 . "LINE") (100 . "AcDbEntity") (8 . "MASONRY") (62 . 7) (370 . 13) (100 . "AcDbLine") (10 10224.3594343891
3759.4273076923 0.0) (11 10224.3594343891 3766.9683257919 0.0))
((0 . "LINE") (100 . "AcDbEntity") (8 . "MASONRY") (62 . 7) (370 . 13) (100 . "AcDbLine") (10 10222.4745248869
3003.3163348416 0.0) (11 10238.8394004525 3003.3163348416 0.0))
((0 . "LINE") (100 . "AcDbEntity") (8 . "MASONRY") (62 . 7) (370 . 13) (100 . "AcDbLine") (10 10238.8394004525
3003.3163348416 0.0) (11 10238.8394004525 2944.946979638 0.0))
((0 . "LINE") (100 . "AcDbEntity") (8 . "MASONRY") (62 . 7) (370 . 13) (100 . "AcDbLine") (10 10226.2443438914
5642.3087104072 0.0) (11 10237.556561086 5642.3087104072 0.0))
((0 . "LINE") (100 . "AcDbEntity") (8 . "MASONRY") (62 . 7) (370 . 13) (100 . "AcDbLine") (10 10230.0141628959
3799.0193778281 0.0) (11 10245.098959276 3799.0193778281 0.0))
((0 . "LINE") (100 . "AcDbEntity") (8 . "MASONRY") (62 . 7) (370 . 13) (100 . "AcDbLine") (10 10245.098959276
3674.5849886878 0.0) (11 10230.0141628959 3674.5849886878 0.0))
((0 . "LINE") (100 . "AcDbEntity") (8 . "MASONRY") (62 . 7) (370 . 13) (100 . "AcDbLine") (10 10335.5966968326
1089.7440497738 0.0) (11 10233.7867420814 1089.7440497738 0.0))
((0 . "LINE") (100 . "AcDbEntity") (8 . "MASONRY") (62 . 7) (370 . 13) (100 . "AcDbLine") (10 10392.1577828054
1003.0175113122 0.0) (11 10233.7867420814 1003.0175113122 0.0))
((0 . "LINE") (100 . "AcDbEntity") (8 . "MASONRY") (62 . 7) (370 . 13) (100 . "AcDbLine") (10 10237.556561086
5642.3087104072 0.0) (11 10237.556561086 5602.1912217195 0.0))
((0 . "LINE") (100 . "AcDbEntity") (8 . "MASONRY") (62 . 7) (370 . 13) (100 . "AcDbLine") (10 10237.556561086
5642.3087104072 0.0) (11 10252.6385972851 5642.3087104072 0.0))
((0 . "LINE") (100 . "AcDbEntity") (8 . "MASONRY") (62 . 7) (370 . 13) (100 . "AcDbLine") (10 10252.6385972851
5642.3087104072 0.0) (11 10392.1577828054 5642.3087104072 0.0))
((0 . "LINE") (100 . "AcDbEntity") (8 . "MASONRY") (62 . 7) (370 . 13) (100 . "AcDbLine") (10 10237.556561086
5602.1912217195 0.0) (11 10237.556561086 5546.7576244344 0.0))
((0 . "LINE") (100 . "AcDbEntity") (8 . "MASONRY") (62 . 7) (370 . 13) (100 . "AcDbLine") (10 10237.556561086
5222.4731447964 0.0) (11 10256.4111764706 5222.4731447964 0.0))
((0 . "LINE") (100 . "AcDbEntity") (8 . "MASONRY") (62 . 7) (370 . 13) (100 . "AcDbLine") (10 10237.556561086
3631.221719457 0.0) (11 10273.3781221719 3631.221719457 0.0))
((0 . "LINE") (100 . "AcDbEntity") (8 . "MASONRY") (62 . 7) (370 . 13) (100 . "AcDbLine") (10 10248.875678733
3061.8403506787 0.0) (11 10248.875678733 3035.5220475113 0.0))
((0 . "LINE") (100 . "AcDbEntity") (8 . "MASONRY") (62 . 7) (370 . 13) (100 . "AcDbLine") (10 10248.875678733
3035.5220475113 0.0) (11 10392.1577828054 3035.5220475113 0.0))
((0 . "LINE") (100 . "AcDbEntity") (8 . "MASONRY") (62 . 7) (370 . 13) (100 . "AcDbLine") (10 10248.875678733
3061.8403506787 0.0) (11 10248.875678733 3099.019321267 0.0))
((0 . "LINE") (100 . "AcDbEntity") (8 . "MASONRY") (62 . 7) (370 . 13) (100 . "AcDbLine") (10 10248.875678733
3099.019321267 0.0) (11 10388.3852036199 3099.019321267 0.0))
((0 . "LINE") (100 . "AcDbEntity") (8 . "MASONRY") (62 . 7) (370 . 13) (100 . "AcDbLine") (10 10241.3263800905
6025.4928054299 0.0) (11 10365.7607692308 6025.4928054299 0.0))
((0 . "LINE") (100 . "AcDbEntity") (8 . "MASONRY") (62 . 7) (370 . 13) (100 . "AcDbLine") (10 10365.7607692308
6025.4928054299 0.0) (11 10383.9387556561 6025.4928054299 0.0))
((0 . "LINE") (100 . "AcDbEntity") (8 . "MASONRY") (62 . 7) (370 . 13) (100 . "AcDbLine") (10 10383.9387556561
6025.4928054299 0.0) (11 10383.9387556561 5995.4751131222 0.0))
((0 . "LINE") (100 . "AcDbEntity") (8 . "MASONRY") (62 . 7) (370 . 13) (100 . "AcDbLine") (10 10331.8241176471
5546.7576244344 0.0) (11 10237.556561086 5546.7576244344 0.0))
((0 . "LINE") (100 . "AcDbEntity") (8 . "MASONRY") (62 . 7) (370 . 13) (100 . "AcDbLine") (10 10241.3263800905
5011.3122171946 0.0) (11 10248.8687782805 5011.3122171946 0.0))
((0 . "LINE") (100 . "AcDbEntity") (8 . "MASONRY") (62 . 7) (370 . 13) (100 . "AcDbLine") (10 10243.2126696833
4920.814479638 0.0) (11 10243.2126696833 4892.5339366516 0.0))
((0 . "LINE") (100 . "AcDbEntity") (8 . "MASONRY") (62 . 7) (370 . 13) (100 . "AcDbLine") (10 10241.3263800905
4690.7989366516 0.0) (11 10241.3263800905 4668.1745022624 0.0))
((0 . "LINE") (100 . "AcDbEntity") (8 . "MASONRY") (62 . 7) (370 . 13) (100 . "AcDbLine") (10 10392.1577828054
4634.2378506787 0.0) (11 10241.3263800905 4634.2378506787 0.0))
((0 . "LINE") (100 . "AcDbEntity") (8 . "MASONRY") (62 . 7) (370 . 13) (100 . "AcDbLine") (10 10241.3263800905
4634.2378506787 0.0) (11 10241.3263800905 4615.3846153846 0.0))
((0 . "LINE") (100 . "AcDbEntity") (8 . "MASONRY") (62 . 7) (370 . 13) (100 . "AcDbLine") (10 10241.3263800905
3506.6326696833 0.0) (11 10241.3263800905 3472.850678733 0.0))
((0 . "LINE") (100 . "AcDbEntity") (8 . "MASONRY") (62 . 7) (370 . 13) (100 . "AcDbLine") (10 10263.9508144796
3506.6326696833 0.0) (11 10241.3263800905 3506.6326696833 0.0))
((0 . "LINE") (100 . "AcDbEntity") (8 . "MASONRY") (62 . 7) (370 . 13) (100 . "AcDbLine") (10 10388.3852036199
3472.850678733 0.0) (11 10241.3263800905 3472.850678733 0.0))
((0 . "LINE") (100 . "AcDbEntity") (8 . "MASONRY") (62 . 7) (370 . 13) (100 . "AcDbLine") (10 10392.1577828054
2944.946979638 0.0) (11 10238.8394004525 2944.946979638 0.0))
((0 . "LINE") (100 . "AcDbEntity") (8 . "MASONRY") (62 . 7) (370 . 13) (100 . "AcDbLine") (10 10245.0975791855
2771.4932126697 0.0) (11 10245.0975791855 2726.2443438914 0.0))
((0 . "LINE") (100 . "AcDbEntity") (8 . "MASONRY") (62 . 7) (370 . 13) (100 . "AcDbLine") (10 10241.3263800905
1730.7692307692 0.0) (11 10346.9089140271 1730.7692307692 0.0))
((0 . "LINE") (100 . "AcDbEntity") (8 . "MASONRY") (62 . 7) (370 . 13) (100 . "AcDbLine") (10 10346.9089140271
1730.7692307692 0.0) (11 10392.1577828054 1730.7692307692 0.0))
((0 . "LINE") (100 . "AcDbEntity") (8 . "MASONRY") (62 . 7) (370 . 13) (100 . "AcDbLine") (10 10388.3852036199
424.2854751131 0.0) (11 10245.1010294118 424.2854751131 0.0))
((0 . "LINE") (100 . "AcDbEntity") (8 . "MASONRY") (62 . 7) (370 . 13) (100 . "AcDbLine") (10 10245.1010294118
424.2854751131 0.0) (11 10245.1010294118 441.1764705882 0.0))
((0 . "LINE") (100 . "AcDbEntity") (8 . "MASONRY") (62 . 7) (370 . 13) (100 . "AcDbLine") (10 10316.742081448
75.4157013575 0.0) (11 10241.3263800905 75.4157013575 0.0))
((0 . "LINE") (100 . "AcDbEntity") (8 . "MASONRY") (62 . 7) (370 . 13) (100 . "AcDbLine") (10 10250.7550678733
5908.7482352941 0.0) (11 10250.7550678733 5946.4553846154 0.0))
((0 . "LINE") (100 . "AcDbEntity") (8 . "MASONRY") (62 . 7) (370 . 13) (100 . "AcDbLine") (10 10250.7550678733
5946.4553846154 0.0) (11 10354.4485520362 5946.4553846154 0.0))
((0 . "LINE") (100 . "AcDbEntity") (8 . "MASONRY") (62 . 7) (370 . 13) (100 . "AcDbLine") (10 10243.2126696833
4892.5339366516 0.0) (11 10388.3852036199 4892.5339366516 0.0))
((0 . "LINE") (100 . "AcDbEntity") (8 . "MASONRY") (62 . 7) (370 . 13) (100 . "AcDbLine") (10 10246.9838687783
4377.8280542986 0.0) (11 10246.9838687783 4402.3380882353 0.0))
((0 . "LINE") (100 . "AcDbEntity") (8 . "MASONRY") (62 . 7) (370 . 13) (100 . "AcDbLine") (10 10286.5752488688
952.1111538462 0.0) (11 10245.098959276 952.1111538462 0.0))
((0 . "LINE") (100 . "AcDbEntity") (8 . "MASONRY") (62 . 7) (370 . 13) (100 . "AcDbLine") (10 10245.098959276
855.9586877828 0.0) (11 10260.1809954751 855.9586877828 0.0))
((0 . "LINE") (100 . "AcDbEntity") (8 . "MASONRY") (62 . 7) (370 . 13) (100 . "AcDbLine") (10 10248.8687782805
4973.6043665158 0.0) (11 10248.8687782805 5011.3122171946 0.0))
((0 . "LINE") (100 . "AcDbEntity") (8 . "MASONRY") (62 . 7) (370 . 13) (100 . "AcDbLine") (10 10279.0356108597
5011.3122171946 0.0) (11 10248.8687782805 5011.3122171946 0.0))
((0 . "LINE") (100 . "AcDbEntity") (8 . "MASONRY") (62 . 7) (370 . 13) (100 . "AcDbLine") (10 10248.8687782805
4973.6043665158 0.0) (11 10388.3852036199 4973.6043665158 0.0))
((0 . "LINE") (100 . "AcDbEntity") (8 . "MASONRY") (62 . 7) (370 . 13) (100 . "AcDbLine") (10 10358.2211312217
4402.3380882353 0.0) (11 10246.9838687783 4402.3380882353 0.0))
((0 . "LINE") (100 . "AcDbEntity") (8 . "MASONRY") (62 . 7) (370 . 13) (100 . "AcDbLine") (10 10250.7536877828
3152.3380882353 0.0) (11 10250.7536877828 3186.274739819 0.0))
((0 . "LINE") (100 . "AcDbEntity") (8 . "MASONRY") (62 . 7) (370 . 13) (100 . "AcDbLine") (10 10245.0975791855
2771.4932126697 0.0) (11 10388.3852036199 2771.4932126697 0.0))
((0 . "LINE") (100 . "AcDbEntity") (8 . "MASONRY") (62 . 7) (370 . 13) (100 . "AcDbLine") (10 10248.8687782805
2692.3076923077 0.0) (11 10388.3852036199 2692.3076923077 0.0))
((0 . "LINE") (100 . "AcDbEntity") (8 . "MASONRY") (62 . 7) (370 . 13) (100 . "AcDbLine") (10 10388.3852036199
3186.274739819 0.0) (11 10250.7536877828 3186.274739819 0.0))
((0 . "LINE") (100 . "AcDbEntity") (8 . "MASONRY") (62 . 7) (370 . 13) (100 . "AcDbLine") (10 10252.6385972851
2654.6005316742 0.0) (11 10252.6385972851 2628.20489819 0.0))
((0 . "LINE") (100 . "AcDbEntity") (8 . "MASONRY") (62 . 7) (370 . 13) (100 . "AcDbLine") (10 10252.6385972851
2628.20489819 0.0) (11 10358.2211312217 2628.20489819 0.0))
((0 . "LINE") (100 . "AcDbEntity") (8 . "MASONRY") (62 . 7) (370 . 13) (100 . "AcDbLine") (10 10260.1809954751
904.9773755656 0.0) (11 10252.6385972851 904.9773755656 0.0))
((0 . "LINE") (100 . "AcDbEntity") (8 . "MASONRY") (62 . 7) (370 . 13) (100 . "AcDbLine") (10 10252.6385972851
816.3645475113 0.0) (11 10365.7607692308 816.3645475113 0.0))
((0 . "LINE") (100 . "AcDbEntity") (8 . "MASONRY") (62 . 7) (370 . 13) (100 . "AcDbLine") (10 10290.3478280543
6308.3690158371 0.0) (11 10267.7233936652 6308.3690158371 0.0))
((0 . "LINE") (100 . "AcDbEntity") (8 . "MASONRY") (62 . 7) (370 . 13) (100 . "AcDbLine") (10 10384.6153846154
3863.1221719457 0.0) (11 10263.9508144796 3863.1221719457 0.0))
((0 . "LINE") (100 . "AcDbEntity") (8 . "MASONRY") (62 . 7) (370 . 13) (100 . "AcDbLine") (10 10267.7233936652
6304.6758371041 0.0) (11 10267.7233936652 6206.6363800905 0.0))
((0 . "LINE") (100 . "AcDbEntity") (8 . "MASONRY") (62 . 7) (370 . 13) (100 . "AcDbLine") (10 10267.7233936652
6304.6758371041 0.0) (11 10290.3478280543 6304.6758371041 0.0))
((0 . "LINE") (100 . "AcDbEntity") (8 . "MASONRY") (62 . 7) (370 . 13) (100 . "AcDbLine") (10 10388.3852036199
6206.6363800905 0.0) (11 10267.7233936652 6206.6363800905 0.0))
((0 . "LINE") (100 . "AcDbEntity") (8 . "MASONRY") (62 . 7) (370 . 13) (100 . "AcDbLine") (10 10273.3781221719
3631.221719457 0.0) (11 10273.3781221719 3593.5145588235 0.0))
((0 . "LINE") (100 . "AcDbEntity") (8 . "MASONRY") (62 . 7) (370 . 13) (100 . "AcDbLine") (10 10328.0542986425
3678.3561877828 0.0) (11 10275.2630316742 3678.3561877828 0.0))
((0 . "LINE") (100 . "AcDbEntity") (8 . "MASONRY") (62 . 7) (370 . 13) (100 . "AcDbLine") (10 10392.1577828054
3631.221719457 0.0) (11 10273.3781221719 3631.221719457 0.0))
((0 . "LINE") (100 . "AcDbEntity") (8 . "MASONRY") (62 . 7) (370 . 13) (100 . "AcDbLine") (10 10275.2630316742
3570.9674547511 0.0) (11 10354.4464819005 3570.9674547511 0.0))
((0 . "LINE") (100 . "AcDbEntity") (8 . "MASONRY") (62 . 7) (370 . 13) (100 . "AcDbLine") (10 10354.4464819005
3570.9674547511 0.0) (11 10354.4464819005 3582.202341629 0.0))
((0 . "LINE") (100 . "AcDbEntity") (8 . "MASONRY") (62 . 7) (370 . 13) (100 . "AcDbLine") (10 10275.2630316742
3527.5268552036 0.0) (11 10354.4485520362 3527.5268552036 0.0))
((0 . "LINE") (100 . "AcDbEntity") (8 . "MASONRY") (62 . 7) (370 . 13) (100 . "AcDbLine") (10 10280.920520362
4170.4369457014 0.0) (11 10280.920520362 4144.0426923077 0.0))
((0 . "LINE") (100 . "AcDbEntity") (8 . "MASONRY") (62 . 7) (370 . 13) (100 . "AcDbLine") (10 10369.5333484163
3791.4783597285 0.0) (11 10279.0356108597 3791.4783597285 0.0))
((0 . "LINE") (100 . "AcDbEntity") (8 . "MASONRY") (62 . 7) (370 . 13) (100 . "AcDbLine") (10 10280.920520362
4144.0426923077 0.0) (11 10388.3852036199 4144.0426923077 0.0))
((0 . "LINE") (100 . "AcDbEntity") (8 . "MASONRY") (62 . 7) (370 . 13) (100 . "AcDbLine") (10 10388.3852036199
6391.4027149321 0.0) (11 10286.5752488688 6391.4027149321 0.0))
((0 . "LINE") (100 . "AcDbEntity") (8 . "MASONRY") (62 . 7) (370 . 13) (100 . "AcDbLine") (10 10286.5752488688
6361.2369230769 0.0) (11 10286.5752488688 6391.4027149321 0.0))
((0 . "LINE") (100 . "AcDbEntity") (8 . "MASONRY") (62 . 7) (370 . 13) (100 . "AcDbLine") (10 10290.3478280543
6308.3690158371 0.0) (11 10290.3478280543 6327.3002714932 0.0))
((0 . "LINE") (100 . "AcDbEntity") (8 . "MASONRY") (62 . 7) (370 . 13) (100 . "AcDbLine") (10 10286.5752488688
4253.3936651584 0.0) (11 10358.2211312217 4253.3936651584 0.0))
((0 . "LINE") (100 . "AcDbEntity") (8 . "MASONRY") (62 . 7) (370 . 13) (100 . "AcDbLine") (10 10288.4615384615
2243.5895135747 0.0) (11 10288.4615384615 2269.9851470588 0.0))
((0 . "LINE") (100 . "AcDbEntity") (8 . "MASONRY") (62 . 7) (370 . 13) (100 . "AcDbLine") (10 10380.8455656109
1185.2958257919 0.0) (11 10290.34989819 1185.2958257919 0.0))
((0 . "LINE") (100 . "AcDbEntity") (8 . "MASONRY") (62 . 7) (370 . 13) (100 . "AcDbLine") (10 10350.6787330317
1219.2352488688 0.0) (11 10290.34989819 1219.2352488688 0.0))
((0 . "LINE") (100 . "AcDbEntity") (8 . "MASONRY") (62 . 7) (370 . 13) (100 . "AcDbLine") (10 10290.34989819
1219.2352488688 0.0) (11 10290.34989819 1185.2958257919 0.0))
((0 . "LINE") (100 . "AcDbEntity") (8 . "MASONRY") (62 . 7) (370 . 13) (100 . "AcDbLine") (10 10388.3852036199
6304.6758371041 0.0) (11 10290.3478280543 6304.6758371041 0.0))
((0 . "LINE") (100 . "AcDbEntity") (8 . "MASONRY") (62 . 7) (370 . 13) (100 . "AcDbLine") (10 10288.4615384615
2269.9851470588 0.0) (11 10388.3852036199 2269.9851470588 0.0))
((0 . "LINE") (100 . "AcDbEntity") (8 . "MASONRY") (62 . 7) (370 . 13) (100 . "AcDbLine") (10 10388.3852036199
4599.7730090498 0.0) (11 10311.0859728507 4599.7730090498 0.0))
((0 . "LINE") (100 . "AcDbEntity") (8 . "MASONRY") (62 . 7) (370 . 13) (100 . "AcDbLine") (10 10311.0859728507
4599.7730090498 0.0) (11 10311.0859728507 4562.5947285068 0.0))
((0 . "LINE") (100 . "AcDbEntity") (8 . "MASONRY") (62 . 7) (370 . 13) (100 . "AcDbLine") (10 10312.9708823529
5041.4776696833 0.0) (11 10312.9708823529 5015.0834162896 0.0))
((0 . "LINE") (100 . "AcDbEntity") (8 . "MASONRY") (62 . 7) (370 . 13) (100 . "AcDbLine") (10 10313.0482126697
1957.0135746606 0.0) (11 10313.0482126697 1984.6920475113 0.0))
((0 . "LINE") (100 . "AcDbEntity") (8 . "MASONRY") (62 . 7) (370 . 13) (100 . "AcDbLine") (10 10313.0482126697
1984.6920475113 0.0) (11 10392.1577828054 1984.6920475113 0.0))
((0 . "LINE") (100 . "AcDbEntity") (8 . "MASONRY") (62 . 7) (370 . 13) (100 . "AcDbLine") (10 10309.1996832579
1864.6309276018 0.0) (11 10309.1996832579 1915.5352149321 0.0))
((0 . "LINE") (100 . "AcDbEntity") (8 . "MASONRY") (62 . 7) (370 . 13) (100 . "AcDbLine") (10 10309.1996832579
1864.6309276018 0.0) (11 10392.1577828054 1864.6309276018 0.0))
((0 . "LINE") (100 . "AcDbEntity") (8 . "MASONRY") (62 . 7) (370 . 13) (100 . "AcDbLine") (10 10388.3852036199
950.2262443439 0.0) (11 10309.1996832579 950.2262443439 0.0))
((0 . "LINE") (100 . "AcDbEntity") (8 . "MASONRY") (62 . 7) (370 . 13) (100 . "AcDbLine") (10 10395.92760181
854.07239819 0.0) (11 10309.1996832579 854.07239819 0.0))
((0 . "LINE") (100 . "AcDbEntity") (8 . "MASONRY") (62 . 7) (370 . 13) (100 . "AcDbLine") (10 10318.6269909502
5064.1021040724 0.0) (11 10318.6269909502 5086.7265384615 0.0))
((0 . "LINE") (100 . "AcDbEntity") (8 . "MASONRY") (62 . 7) (370 . 13) (100 . "AcDbLine") (10 10316.742081448
75.4157013575 0.0) (11 10316.742081448 177.2256561086 0.0))
((0 . "LINE") (100 . "AcDbEntity") (8 . "MASONRY") (62 . 7) (370 . 13) (100 . "AcDbLine") (10 10392.1577828054
177.2256561086 0.0) (11 10316.742081448 177.2256561086 0.0))
((0 . "LINE") (100 . "AcDbEntity") (8 . "MASONRY") (62 . 7) (370 . 13) (100 . "AcDbLine") (10 10316.742081448
75.4157013575 0.0) (11 10384.6153846154 75.4157013575 0.0))
((0 . "LINE") (100 . "AcDbEntity") (8 . "MASONRY") (62 . 7) (370 . 13) (100 . "AcDbLine") (10 10384.6153846154
4074.2837895928 0.0) (11 10320.5119004525 4074.2837895928 0.0))
((0 . "LINE") (100 . "AcDbEntity") (8 . "MASONRY") (62 . 7) (370 . 13) (100 . "AcDbLine") (10 10322.3981900452
614.6295475113 0.0) (11 10322.3981900452 592.0051131222 0.0))
((0 . "LINE") (100 . "AcDbEntity") (8 . "MASONRY") (62 . 7) (370 . 13) (100 . "AcDbLine") (10 10318.7788914027
3989.4414705882 0.0) (11 10392.1577828054 3989.4414705882 0.0))
((0 . "LINE") (100 . "AcDbEntity") (8 . "MASONRY") (62 . 7) (370 . 13) (100 . "AcDbLine") (10 10324.284479638
671.1906334842 0.0) (11 10324.284479638 678.7330316742 0.0))
((0 . "LINE") (100 . "AcDbEntity") (8 . "MASONRY") (62 . 7) (370 . 13) (100 . "AcDbLine") (10 10324.284479638
565.6108597285 0.0) (11 10324.284479638 537.3303167421 0.0))
((0 . "LINE") (100 . "AcDbEntity") (8 . "MASONRY") (62 . 7) (370 . 13) (100 . "AcDbLine") (10 10388.3852036199
537.3303167421 0.0) (11 10324.284479638 537.3303167421 0.0))
((0 . "LINE") (100 . "AcDbEntity") (8 . "MASONRY") (62 . 7) (370 . 13) (100 . "AcDbLine") (10 10358.2211312217
4483.4092081448 0.0) (11 10328.0542986425 4483.4092081448 0.0))
((0 . "LINE") (100 . "AcDbEntity") (8 . "MASONRY") (62 . 7) (370 . 13) (100 . "AcDbLine") (10 10329.9392081448
2907.2398190045 0.0) (11 10329.9392081448 2892.1570927602 0.0))
((0 . "LINE") (100 . "AcDbEntity") (8 . "MASONRY") (62 . 7) (370 . 13) (100 . "AcDbLine") (10 10331.8241176471
2021.1163687783 0.0) (11 10331.8241176471 2045.7037330317 0.0))
((0 . "LINE") (100 . "AcDbEntity") (8 . "MASONRY") (62 . 7) (370 . 13) (100 . "AcDbLine") (10 10331.8241176471
2045.7037330317 0.0) (11 10331.8241176471 2055.053020362 0.0))
((0 . "LINE") (100 . "AcDbEntity") (8 . "MASONRY") (62 . 7) (370 . 13) (100 . "AcDbLine") (10 10350.6787330317
2055.053020362 0.0) (11 10331.8241176471 2055.053020362 0.0))
((0 . "LINE") (100 . "AcDbEntity") (8 . "MASONRY") (62 . 7) (370 . 13) (100 . "AcDbLine") (10 10331.8241176471
2055.053020362 0.0) (11 10331.8241176471 2147.3590271493 0.0))
((0 . "LINE") (100 . "AcDbEntity") (8 . "MASONRY") (62 . 7) (370 . 13) (100 . "AcDbLine") (10 10331.8241176471
2147.3590271493 0.0) (11 10388.3852036199 2147.3590271493 0.0))
((0 . "LINE") (100 . "AcDbEntity") (8 . "MASONRY") (62 . 7) (370 . 13) (100 . "AcDbLine") (10 10343.1363348416
5403.4686199095 0.0) (11 10335.5966968326 5403.4686199095 0.0))
((0 . "LINE") (100 . "AcDbEntity") (8 . "MASONRY") (62 . 7) (370 . 13) (100 . "AcDbLine") (10 10335.5966968326
2835.5960067873 0.0) (11 10335.5966968326 2824.2837895928 0.0))
((0 . "LINE") (100 . "AcDbEntity") (8 . "MASONRY") (62 . 7) (370 . 13) (100 . "AcDbLine") (10 10341.2583257919
3291.8552036199 0.0) (11 10341.2583257919 3275.4889479638 0.0))
((0 . "LINE") (100 . "AcDbEntity") (8 . "MASONRY") (62 . 7) (370 . 13) (100 . "AcDbLine") (10 10341.2583257919
3275.4889479638 0.0) (11 10388.3852036199 3275.4889479638 0.0))
((0 . "LINE") (100 . "AcDbEntity") (8 . "MASONRY") (62 . 7) (370 . 13) (100 . "AcDbLine") (10 10345.0226244344
5727.752760181 0.0) (11 10392.1577828054 5727.752760181 0.0))
((0 . "LINE") (100 . "AcDbEntity") (8 . "MASONRY") (62 . 7) (370 . 13) (100 . "AcDbLine") (10 10345.0226244344
5746.6063348416 0.0) (11 10345.0226244344 5727.752760181 0.0))
((0 . "LINE") (100 . "AcDbEntity") (8 . "MASONRY") (62 . 7) (370 . 13) (100 . "AcDbLine") (10 10348.7924434389
1595.0226244344 0.0) (11 10348.7924434389 1561.0859728507 0.0))
((0 . "LINE") (100 . "AcDbEntity") (8 . "MASONRY") (62 . 7) (370 . 13) (100 . "AcDbLine") (10 10343.1363348416
1478.1306334842 0.0) (11 10343.1363348416 1440.4214027149 0.0))
((0 . "LINE") (100 . "AcDbEntity") (8 . "MASONRY") (62 . 7) (370 . 13) (100 . "AcDbLine") (10 10388.3852036199
1440.4214027149 0.0) (11 10343.1363348416 1440.4214027149 0.0))
((0 . "LINE") (100 . "AcDbEntity") (8 . "MASONRY") (62 . 7) (370 . 13) (100 . "AcDbLine") (10 10354.4485520362
245.098959276 0.0) (11 10354.4485520362 260.1809954751 0.0))
((0 . "LINE") (100 . "AcDbEntity") (8 . "MASONRY") (62 . 7) (370 . 13) (100 . "AcDbLine") (10 10354.4485520362
260.1809954751 0.0) (11 10354.4485520362 354.4485520362 0.0))
((0 . "LINE") (100 . "AcDbEntity") (8 . "MASONRY") (62 . 7) (370 . 13) (100 . "AcDbLine") (10 10392.1577828054
4515.460260181 0.0) (11 10350.6787330317 4515.460260181 0.0))
((0 . "LINE") (100 . "AcDbEntity") (8 . "MASONRY") (62 . 7) (370 . 13) (100 . "AcDbLine") (10 10392.1577828054
5135.5919457014 0.0) (11 10354.4485520362 5135.5919457014 0.0))
((0 . "LINE") (100 . "AcDbEntity") (8 . "MASONRY") (62 . 7) (370 . 13) (100 . "AcDbLine") (10 10354.4485520362
3674.5849886878 0.0) (11 10380.8455656109 3674.5849886878 0.0))
((0 . "LINE") (100 . "AcDbEntity") (8 . "MASONRY") (62 . 7) (370 . 13) (100 . "AcDbLine") (10 10395.92760181
1595.0226244344 0.0) (11 10348.7924434389 1595.0226244344 0.0))
((0 . "LINE") (100 . "AcDbEntity") (8 . "MASONRY") (62 . 7) (370 . 13) (100 . "AcDbLine") (10 10388.3852036199
354.4485520362 0.0) (11 10354.4485520362 354.4485520362 0.0))
((0 . "LINE") (100 . "AcDbEntity") (8 . "MASONRY") (62 . 7) (370 . 13) (100 . "AcDbLine") (10 10388.3852036199
5190.4220927602 0.0) (11 10358.2211312217 5190.4220927602 0.0))
((0 . "LINE") (100 . "AcDbEntity") (8 . "MASONRY") (62 . 7) (370 . 13) (100 . "AcDbLine") (10 10358.2211312217
4402.3380882353 0.0) (11 10358.2211312217 4434.3891402715 0.0))
((0 . "LINE") (100 . "AcDbEntity") (8 . "MASONRY") (62 . 7) (370 . 13) (100 . "AcDbLine") (10 10358.2211312217
4402.3380882353 0.0) (11 10384.6153846154 4402.3380882353 0.0))
((0 . "LINE") (100 . "AcDbEntity") (8 . "MASONRY") (62 . 7) (370 . 13) (100 . "AcDbLine") (10 10377.0729864253
1093.5152488688 0.0) (11 10358.2211312217 1093.5152488688 0.0))
((0 . "LINE") (100 . "AcDbEntity") (8 . "MASONRY") (62 . 7) (370 . 13) (100 . "AcDbLine") (10 10392.1577828054
2518.8539253394 0.0) (11 10363.8758597285 2518.8539253394 0.0))
((0 . "LINE") (100 . "AcDbEntity") (8 . "MASONRY") (62 . 7) (370 . 13) (100 . "AcDbLine") (10 10363.8758597285
2575.4150113122 0.0) (11 10363.8758597285 2518.8539253394 0.0))
((0 . "LINE") (100 . "AcDbEntity") (8 . "MASONRY") (62 . 7) (370 . 13) (100 . "AcDbLine") (10 10378.9592760181
5542.9864253394 0.0) (11 10365.7607692308 5542.9864253394 0.0))
((0 . "LINE") (100 . "AcDbEntity") (8 . "MASONRY") (62 . 7) (370 . 13) (100 . "AcDbLine") (10 10384.6153846154
4800.1505995475 0.0) (11 10373.3031674208 4800.1505995475 0.0))
((0 . "LINE") (100 . "AcDbEntity") (8 . "MASONRY") (62 . 7) (370 . 13) (100 . "AcDbLine") (10 10392.1577828054
2056.9386199095 0.0) (11 10373.3031674208 2056.9386199095 0.0))
((0 . "LINE") (100 . "AcDbEntity") (8 . "MASONRY") (62 . 7) (370 . 13) (100 . "AcDbLine") (10 10392.1577828054
5944.5701357466 0.0) (11 10377.0729864253 5944.5701357466 0.0))
((0 . "LINE") (100 . "AcDbEntity") (8 . "MASONRY") (62 . 7) (370 . 13) (100 . "AcDbLine") (10 10378.9592760181
5542.9864253394 0.0) (11 10378.9592760181 5512.8209728507 0.0))
((0 . "LINE") (100 . "AcDbEntity") (8 . "MASONRY") (62 . 7) (370 . 13) (100 . "AcDbLine") (10 10384.6153846154
5542.9864253394 0.0) (11 10378.9592760181 5542.9864253394 0.0))
((0 . "LINE") (100 . "AcDbEntity") (8 . "MASONRY") (62 . 7) (370 . 13) (100 . "AcDbLine") (10 10377.0729864253
5488.3102488688 0.0) (11 10395.92760181 5488.3102488688 0.0))
((0 . "LINE") (100 . "AcDbEntity") (8 . "MASONRY") (62 . 7) (370 . 13) (100 . "AcDbLine") (10 10377.0729864253
4864.2533936652 0.0) (11 10377.0729864253 4845.400158371 0.0))
((0 . "LINE") (100 . "AcDbEntity") (8 . "MASONRY") (62 . 7) (370 . 13) (100 . "AcDbLine") (10 10377.0729864253
3930.9954751131 0.0) (11 10388.3852036199 3930.9954751131 0.0))
((0 . "LINE") (100 . "AcDbEntity") (8 . "MASONRY") (62 . 7) (370 . 13) (100 . "AcDbLine") (10 10377.0729864253
1342.3840271493 0.0) (11 10377.0729864253 1312.2171945701 0.0))
((0 . "LINE") (100 . "AcDbEntity") (8 . "MASONRY") (62 . 7) (370 . 13) (100 . "AcDbLine") (10 10377.0729864253
1342.3840271493 0.0) (11 10392.1577828054 1342.3840271493 0.0))
((0 . "LINE") (100 . "AcDbEntity") (8 . "MASONRY") (62 . 7) (370 . 13) (100 . "AcDbLine") (10 10377.0729864253
1093.5152488688 0.0) (11 10377.0729864253 1157.6159728507 0.0))
((0 . "LINE") (100 . "AcDbEntity") (8 . "MASONRY") (62 . 7) (370 . 13) (100 . "AcDbLine") (10 10392.1577828054
1093.5152488688 0.0) (11 10377.0729864253 1093.5152488688 0.0))
((0 . "LINE") (100 . "AcDbEntity") (8 . "MASONRY") (62 . 7) (370 . 13) (100 . "AcDbLine") (10 10380.8455656109
814.479638009 0.0) (11 10395.92760181 814.479638009 0.0))
((0 . "LINE") (100 . "AcDbEntity") (8 . "MASONRY") (62 . 7) (370 . 13) (100 . "AcDbLine") (10 10392.1564027149
5920.0604524887 0.0) (11 10392.1564027149 5874.8115837104 0.0))
((0 . "LINE") (100 . "AcDbEntity") (8 . "MASONRY") (62 . 7) (370 . 13) (100 . "AcDbLine") (10 10395.92760181
4766.214638009 0.0) (11 10395.92760181 4777.5268552036 0.0))
((0 . "LINE") (100 . "AcDbEntity") (8 . "MASONRY") (62 . 7) (370 . 13) (100 . "AcDbLine") (10 12051.2825113122
2820.5125904977 0.0) (11 12051.2825113122 2707.390418552 0.0))
((0 . "LINE") (100 . "AcDbEntity") (8 . "MASONRY") (62 . 7) (370 . 13) (100 . "AcDbLine") (10 12051.2825113122
2820.5125904977 0.0) (11 12051.2825113122 3580.3167420814 0.0))
((0 . "LINE") (100 . "AcDbEntity") (8 . "MASONRY") (62 . 7) (370 . 13) (100 . "AcDbLine") (10 12051.2825113122
2707.390418552 0.0) (11 12051.2825113122 2096.5306900452 0.0))
((0 . "LINE") (100 . "AcDbEntity") (8 . "MASONRY") (62 . 7) (370 . 13) (100 . "AcDbLine") (10 12051.2825113122
220.5882352941 0.0) (11 12051.2825113122 369.5333484163 0.0))
((0 . "LINE") (100 . "AcDbEntity") (8 . "MASONRY") (62 . 7) (370 . 13) (100 . "AcDbLine") (10 12051.2825113122
369.5333484163 0.0) (11 12051.2825113122 652.3387782805 0.0))
((0 . "LINE") (100 . "AcDbEntity") (8 . "MASONRY") (62 . 7) (370 . 13) (100 . "AcDbLine") (10 12051.2825113122
652.3387782805 0.0) (11 12051.2825113122 2096.5306900452 0.0))
((0 . "LINE") (100 . "AcDbEntity") (8 . "MASONRY") (62 . 7) (370 . 13) (100 . "AcDbLine") (10 12104.07239819
3476.6211877828 0.0) (11 12341.628959276 3476.6211877828 0.0))
((0 . "LINE") (100 . "AcDbEntity") (8 . "MASONRY") (62 . 7) (370 . 13) (100 . "AcDbLine") (10 12341.628959276
3476.6211877828 0.0) (11 13118.4007466063 3476.6211877828 0.0))
((0 . "LINE") (100 . "AcDbEntity") (8 . "MASONRY") (62 . 7) (370 . 13) (100 . "AcDbLine") (10 12122.9256334842
2034.3141855204 0.0) (11 12104.07239819 2034.3141855204 0.0))
((0 . "LINE") (100 . "AcDbEntity") (8 . "MASONRY") (62 . 7) (370 . 13) (100 . "AcDbLine") (10 12179.486719457
1972.096300905 0.0) (11 12104.07239819 1972.096300905 0.0))
((0 . "LINE") (100 . "AcDbEntity") (8 . "MASONRY") (62 . 7) (370 . 13) (100 . "AcDbLine") (10 12130.4680316742
1344.2689366516 0.0) (11 12104.07239819 1344.2689366516 0.0))
((0 . "LINE") (100 . "AcDbEntity") (8 . "MASONRY") (62 . 7) (370 . 13) (100 . "AcDbLine") (10 12104.07239819
444.9462895928 0.0) (11 12104.07239819 452.4886877828 0.0))
((0 . "LINE") (100 . "AcDbEntity") (8 . "MASONRY") (62 . 7) (370 . 13) (100 . "AcDbLine") (10 12219.0808597285
2903.4693099548 0.0) (11 12107.8435972851 2903.4693099548 0.0))
((0 . "LINE") (100 . "AcDbEntity") (8 . "MASONRY") (62 . 7) (370 . 13) (100 . "AcDbLine") (10 12107.8435972851
2756.4097963801 0.0) (11 12322.7757239819 2756.4097963801 0.0))
((0 . "LINE") (100 . "AcDbEntity") (8 . "MASONRY") (62 . 7) (370 . 13) (100 . "AcDbLine") (10 12107.8435972851
2654.599841629 0.0) (11 12138.0090497738 2654.599841629 0.0))
((0 . "LINE") (100 . "AcDbEntity") (8 . "MASONRY") (62 . 7) (370 . 13) (100 . "AcDbLine") (10 12428.3554977376
2584.8416289593 0.0) (11 12281.2966742081 2584.8416289593 0.0))
((0 . "LINE") (100 . "AcDbEntity") (8 . "MASONRY") (62 . 7) (370 . 13) (100 . "AcDbLine") (10 12281.2966742081
2584.8416289593 0.0) (11 12107.8435972851 2584.8416289593 0.0))
((0 . "LINE") (100 . "AcDbEntity") (8 . "MASONRY") (62 . 7) (370 . 13) (100 . "AcDbLine") (10 12107.8435972851
2386.8778280543 0.0) (11 12213.4247511312 2386.8778280543 0.0))
((0 . "LINE") (100 . "AcDbEntity") (8 . "MASONRY") (62 . 7) (370 . 13) (100 . "AcDbLine") (10 12107.8435972851
2247.3607126697 0.0) (11 12413.2734615385 2247.3607126697 0.0))
((0 . "LINE") (100 . "AcDbEntity") (8 . "MASONRY") (62 . 7) (370 . 13) (100 . "AcDbLine") (10 12119.1558144796
1644.0413122172 0.0) (11 12107.8435972851 1644.0413122172 0.0))
((0 . "LINE") (100 . "AcDbEntity") (8 . "MASONRY") (62 . 7) (370 . 13) (100 . "AcDbLine") (10 12209.6535520362
1430.9954751131 0.0) (11 12107.8435972851 1430.9954751131 0.0))
((0 . "LINE") (100 . "AcDbEntity") (8 . "MASONRY") (62 . 7) (370 . 13) (100 . "AcDbLine") (10 12128.5831221719
1242.4589819005 0.0) (11 12107.8435972851 1242.4589819005 0.0))
((0 . "LINE") (100 . "AcDbEntity") (8 . "MASONRY") (62 . 7) (370 . 13) (100 . "AcDbLine") (10 12317.1182352941
1180.2404072398 0.0) (11 12107.8435972851 1180.2404072398 0.0))
((0 . "LINE") (100 . "AcDbEntity") (8 . "MASONRY") (62 . 7) (370 . 13) (100 . "AcDbLine") (10 12107.8435972851
955.8823529412 0.0) (11 12236.0478054299 955.8823529412 0.0))
((0 . "LINE") (100 . "AcDbEntity") (8 . "MASONRY") (62 . 7) (370 . 13) (100 . "AcDbLine") (10 12107.8435972851
788.0853846154 0.0) (11 12285.0678733032 788.0853846154 0.0))
((0 . "LINE") (100 . "AcDbEntity") (8 . "MASONRY") (62 . 7) (370 . 13) (100 . "AcDbLine") (10 12107.8435972851
725.8668099548 0.0) (11 12149.3212669683 725.8668099548 0.0))
((0 . "LINE") (100 . "AcDbEntity") (8 . "MASONRY") (62 . 7) (370 . 13) (100 . "AcDbLine") (10 12319.0045248869
3265.460260181 0.0) (11 12111.6134162896 3265.460260181 0.0))
((0 . "LINE") (100 . "AcDbEntity") (8 . "MASONRY") (62 . 7) (370 . 13) (100 . "AcDbLine") (10 12177.6018099548
3190.0452488688 0.0) (11 12111.6134162896 3190.0452488688 0.0))
((0 . "LINE") (100 . "AcDbEntity") (8 . "MASONRY") (62 . 7) (370 . 13) (100 . "AcDbLine") (10 12187.0291176471
3042.9864253394 0.0) (11 12111.6134162896 3042.9864253394 0.0))
((0 . "LINE") (100 . "AcDbEntity") (8 . "MASONRY") (62 . 7) (370 . 13) (100 . "AcDbLine") (10 12220.9657692308
2997.7375565611 0.0) (11 12220.9657692308 2971.4199434389 0.0))
((0 . "LINE") (100 . "AcDbEntity") (8 . "MASONRY") (62 . 7) (370 . 13) (100 . "AcDbLine") (10 12220.9657692308
2971.4199434389 0.0) (11 12111.6134162896 2971.4199434389 0.0))
((0 . "LINE") (100 . "AcDbEntity") (8 . "MASONRY") (62 . 7) (370 . 13) (100 . "AcDbLine") (10 12324.6606334842
2505.5815384615 0.0) (11 12111.6134162896 2505.5815384615 0.0))
((0 . "LINE") (100 . "AcDbEntity") (8 . "MASONRY") (62 . 7) (370 . 13) (100 . "AcDbLine") (10 12138.0090497738
2303.9217986425 0.0) (11 12111.6134162896 2303.9217986425 0.0))
((0 . "LINE") (100 . "AcDbEntity") (8 . "MASONRY") (62 . 7) (370 . 13) (100 . "AcDbLine") (10 12434.0129864253
1907.9941968326 0.0) (11 12111.6134162896 1907.9941968326 0.0))
((0 . "LINE") (100 . "AcDbEntity") (8 . "MASONRY") (62 . 7) (370 . 13) (100 . "AcDbLine") (10 12111.6134162896
1742.0814479638 0.0) (11 12251.1312217195 1742.0814479638 0.0))
((0 . "LINE") (100 . "AcDbEntity") (8 . "MASONRY") (62 . 7) (370 . 13) (100 . "AcDbLine") (10 12111.6134162896
1595.0226244344 0.0) (11 12424.585678733 1595.0226244344 0.0))
((0 . "LINE") (100 . "AcDbEntity") (8 . "MASONRY") (62 . 7) (370 . 13) (100 . "AcDbLine") (10 12111.6134162896
1033.1815837104 0.0) (11 12317.7203054299 1033.1815837104 0.0))
((0 . "LINE") (100 . "AcDbEntity") (8 . "MASONRY") (62 . 7) (370 . 13) (100 . "AcDbLine") (10 12122.9256334842
586.3503846154 0.0) (11 12111.6134162896 586.3503846154 0.0))
((0 . "LINE") (100 . "AcDbEntity") (8 . "MASONRY") (62 . 7) (370 . 13) (100 . "AcDbLine") (10 12307.6923076923
1242.4589819005 0.0) (11 12128.5831221719 1242.4589819005 0.0))
((0 . "LINE") (100 . "AcDbEntity") (8 . "MASONRY") (62 . 7) (370 . 13) (100 . "AcDbLine") (10 12128.5831221719
1242.4589819005 0.0) (11 12128.5831221719 1278.2805429864 0.0))
((0 . "LINE") (100 . "AcDbEntity") (8 . "MASONRY") (62 . 7) (370 . 13) (100 . "AcDbLine") (10 12126.6968325792
321.9307579186 0.0) (11 12141.0552828054 321.9307579186 0.0))
((0 . "LINE") (100 . "AcDbEntity") (8 . "MASONRY") (62 . 7) (370 . 13) (100 . "AcDbLine") (10 12130.4680316742
1344.2689366516 0.0) (11 12130.4680316742 1323.5294117647 0.0))
((0 . "LINE") (100 . "AcDbEntity") (8 . "MASONRY") (62 . 7) (370 . 13) (100 . "AcDbLine") (10 12718.7033257919
1344.2689366516 0.0) (11 12130.4680316742 1344.2689366516 0.0))
((0 . "LINE") (100 . "AcDbEntity") (8 . "MASONRY") (62 . 7) (370 . 13) (100 . "AcDbLine") (10 12134.2378506787
2714.9321266968 0.0) (11 12134.2378506787 2722.4738348416 0.0))
((0 . "LINE") (100 . "AcDbEntity") (8 . "MASONRY") (62 . 7) (370 . 13) (100 . "AcDbLine") (10 12428.3554977376
2630.0904977376 0.0) (11 12138.0090497738 2630.0904977376 0.0))
((0 . "LINE") (100 . "AcDbEntity") (8 . "MASONRY") (62 . 7) (370 . 13) (100 . "AcDbLine") (10 12138.0090497738
2630.0904977376 0.0) (11 12138.0090497738 2654.599841629 0.0))
((0 . "LINE") (100 . "AcDbEntity") (8 . "MASONRY") (62 . 7) (370 . 13) (100 . "AcDbLine") (10 12138.0090497738
2669.6832579186 0.0) (11 12138.0090497738 2654.599841629 0.0))
((0 . "LINE") (100 . "AcDbEntity") (8 . "MASONRY") (62 . 7) (370 . 13) (100 . "AcDbLine") (10 12141.7802488688
2032.4285859729 0.0) (11 12134.2378506787 2032.4285859729 0.0))
((0 . "LINE") (100 . "AcDbEntity") (8 . "MASONRY") (62 . 7) (370 . 13) (100 . "AcDbLine") (10 12127.8982013575
223.4149095023 0.0) (11 12122.2448529412 223.4149095023 0.0))
((0 . "LINE") (100 . "AcDbEntity") (8 . "MASONRY") (62 . 7) (370 . 13) (100 . "AcDbLine") (10 12153.0924660634
2303.9217986425 0.0) (11 12138.0090497738 2303.9217986425 0.0))
((0 . "LINE") (100 . "AcDbEntity") (8 . "MASONRY") (62 . 7) (370 . 13) (100 . "AcDbLine") (10 12256.7873303167
2303.9217986425 0.0) (11 12153.0924660634 2303.9217986425 0.0))
((0 . "LINE") (100 . "AcDbEntity") (8 . "MASONRY") (62 . 7) (370 . 13) (100 . "AcDbLine") (10 12247.3600226244
1666.5124660633 0.0) (11 12164.4046832579 1666.5124660633 0.0))
((0 . "LINE") (100 . "AcDbEntity") (8 . "MASONRY") (62 . 7) (370 . 13) (100 . "AcDbLine") (10 12164.4046832579
1666.5124660633 0.0) (11 12141.7802488688 1666.5124660633 0.0))
((0 . "LINE") (100 . "AcDbEntity") (8 . "MASONRY") (62 . 7) (370 . 13) (100 . "AcDbLine") (10 12175.7169004525
3386.1234502262 0.0) (11 12254.9024208145 3386.1234502262 0.0))
((0 . "LINE") (100 . "AcDbEntity") (8 . "MASONRY") (62 . 7) (370 . 13) (100 . "AcDbLine") (10 12481.1467647059
3190.0452488688 0.0) (11 12285.0678733032 3190.0452488688 0.0))
((0 . "LINE") (100 . "AcDbEntity") (8 . "MASONRY") (62 . 7) (370 . 13) (100 . "AcDbLine") (10 12285.0678733032
3190.0452488688 0.0) (11 12177.6018099548 3190.0452488688 0.0))
((0 . "LINE") (100 . "AcDbEntity") (8 . "MASONRY") (62 . 7) (370 . 13) (100 . "AcDbLine") (10 12177.6018099548
3212.6696832579 0.0) (11 12177.6018099548 3190.0452488688 0.0))
((0 . "LINE") (100 . "AcDbEntity") (8 . "MASONRY") (62 . 7) (370 . 13) (100 . "AcDbLine") (10 12175.7169004525
2036.1990950226 0.0) (11 12183.257918552 2036.1990950226 0.0))
((0 . "LINE") (100 . "AcDbEntity") (8 . "MASONRY") (62 . 7) (370 . 13) (100 . "AcDbLine") (10 12185.1442081448
554.2986425339 0.0) (11 12185.1442081448 588.2352941176 0.0))
((0 . "LINE") (100 . "AcDbEntity") (8 . "MASONRY") (62 . 7) (370 . 13) (100 . "AcDbLine") (10 12183.257918552
2036.1990950226 0.0) (11 12183.257918552 2021.1163687783 0.0))
((0 . "LINE") (100 . "AcDbEntity") (8 . "MASONRY") (62 . 7) (370 . 13) (100 . "AcDbLine") (10 12183.257918552
2036.1990950226 0.0) (11 12203.9960633484 2036.1990950226 0.0))
((0 . "LINE") (100 . "AcDbEntity") (8 . "MASONRY") (62 . 7) (370 . 13) (100 . "AcDbLine") (10 12420.814479638
2088.9896719457 0.0) (11 12198.3413348416 2088.9896719457 0.0))
((0 . "LINE") (100 . "AcDbEntity") (8 . "MASONRY") (62 . 7) (370 . 13) (100 . "AcDbLine") (10 12198.3413348416
727.751719457 0.0) (11 12277.5268552036 727.751719457 0.0))
((0 . "LINE") (100 . "AcDbEntity") (8 . "MASONRY") (62 . 7) (370 . 13) (100 . "AcDbLine") (10 12203.9960633484
2051.281821267 0.0) (11 12203.9960633484 2036.1990950226 0.0))
((0 . "LINE") (100 . "AcDbEntity") (8 . "MASONRY") (62 . 7) (370 . 13) (100 . "AcDbLine") (10 12251.1312217195
3525.6412556561 0.0) (11 12205.8823529412 3525.6412556561 0.0))
((0 . "LINE") (100 . "AcDbEntity") (8 . "MASONRY") (62 . 7) (370 . 13) (100 . "AcDbLine") (10 12349.1699773756
2036.1990950226 0.0) (11 12203.9960633484 2036.1990950226 0.0))
((0 . "LINE") (100 . "AcDbEntity") (8 . "MASONRY") (62 . 7) (370 . 13) (100 . "AcDbLine") (10 12213.4247511312
2386.8778280543 0.0) (11 12213.4247511312 2360.4828846154 0.0))
((0 . "LINE") (100 . "AcDbEntity") (8 . "MASONRY") (62 . 7) (370 . 13) (100 . "AcDbLine") (10 12537.7078506787
3044.8713348416 0.0) (11 12217.1945701357 3044.8713348416 0.0))
((0 . "LINE") (100 . "AcDbEntity") (8 . "MASONRY") (62 . 7) (370 . 13) (100 . "AcDbLine") (10 12219.0808597285
2903.4693099548 0.0) (11 12224.7355882353 2903.4693099548 0.0))
((0 . "LINE") (100 . "AcDbEntity") (8 . "MASONRY") (62 . 7) (370 . 13) (100 . "AcDbLine") (10 12219.0808597285
2903.4693099548 0.0) (11 12219.0808597285 2937.4059615385 0.0))
((0 . "LINE") (100 . "AcDbEntity") (8 . "MASONRY") (62 . 7) (370 . 13) (100 . "AcDbLine") (10 12213.4247511312
2386.8778280543 0.0) (11 12254.9051809955 2386.8778280543 0.0))
((0 . "LINE") (100 . "AcDbEntity") (8 . "MASONRY") (62 . 7) (370 . 13) (100 . "AcDbLine") (10 12254.9051809955
2386.8778280543 0.0) (11 12254.9051809955 2368.1019230769 0.0))
((0 . "LINE") (100 . "AcDbEntity") (8 . "MASONRY") (62 . 7) (370 . 13) (100 . "AcDbLine") (10 12254.9051809955
2368.1019230769 0.0) (11 12533.9366515837 2368.1019230769 0.0))
((0 . "LINE") (100 . "AcDbEntity") (8 . "MASONRY") (62 . 7) (370 . 13) (100 . "AcDbLine") (10 12579.185520362
1436.6515837104 0.0) (11 12232.2779864253 1436.6515837104 0.0))
((0 . "LINE") (100 . "AcDbEntity") (8 . "MASONRY") (62 . 7) (370 . 13) (100 . "AcDbLine") (10 12239.8190045249
590.1202036199 0.0) (11 12266.2146380091 590.1202036199 0.0))
((0 . "LINE") (100 . "AcDbEntity") (8 . "MASONRY") (62 . 7) (370 . 13) (100 . "AcDbLine") (10 12386.8778280543
1817.4971493213 0.0) (11 12247.3600226244 1817.4971493213 0.0))
((0 . "LINE") (100 . "AcDbEntity") (8 . "MASONRY") (62 . 7) (370 . 13) (100 . "AcDbLine") (10 12251.1312217195
957.6913122172 0.0) (11 12430.2404072398 957.6913122172 0.0))
((0 . "LINE") (100 . "AcDbEntity") (8 . "MASONRY") (62 . 7) (370 . 13) (100 . "AcDbLine") (10 12430.2404072398
957.6913122172 0.0) (11 12430.2404072398 901.8096266968 0.0))
((0 . "LINE") (100 . "AcDbEntity") (8 . "MASONRY") (62 . 7) (370 . 13) (100 . "AcDbLine") (10 12430.2404072398
901.8096266968 0.0) (11 12500 901.8096266968 0.0))
((0 . "LINE") (100 . "AcDbEntity") (8 . "MASONRY") (62 . 7) (370 . 13) (100 . "AcDbLine") (10 12256.7873303167
2303.9217986425 0.0) (11 12281.2966742081 2303.9217986425 0.0))
((0 . "LINE") (100 . "AcDbEntity") (8 . "MASONRY") (62 . 7) (370 . 13) (100 . "AcDbLine") (10 12256.7873303167
2326.5462330317 0.0) (11 12256.7873303167 2303.9217986425 0.0))
((0 . "LINE") (100 . "AcDbEntity") (8 . "MASONRY") (62 . 7) (370 . 13) (100 . "AcDbLine") (10 12405.7310633484
2899.6981108597 0.0) (11 12258.672239819 2899.6981108597 0.0))
((0 . "LINE") (100 . "AcDbEntity") (8 . "MASONRY") (62 . 7) (370 . 13) (100 . "AcDbLine") (10 12266.2132579186
837.1040723982 0.0) (11 12266.2132579186 861.5347058824 0.0))
((0 . "LINE") (100 . "AcDbEntity") (8 . "MASONRY") (62 . 7) (370 . 13) (100 . "AcDbLine") (10 12266.2132579186
861.5347058824 0.0) (11 12321.085520362 861.5347058824 0.0))
((0 . "LINE") (100 . "AcDbEntity") (8 . "MASONRY") (62 . 7) (370 . 13) (100 . "AcDbLine") (10 12327.3878846154
865.3832352941 0.0) (11 12496.228800905 865.3832352941 0.0))
((0 . "LINE") (100 . "AcDbEntity") (8 . "MASONRY") (62 . 7) (370 . 13) (100 . "AcDbLine") (10 12268.0995475113
1466.8184162896 0.0) (11 12268.0995475113 1474.3580542986 0.0))
((0 . "LINE") (100 . "AcDbEntity") (8 . "MASONRY") (62 . 7) (370 . 13) (100 . "AcDbLine") (10 12426.4705882353
1530.9191402715 0.0) (11 12269.9844570136 1530.9191402715 0.0))
((0 . "LINE") (100 . "AcDbEntity") (8 . "MASONRY") (62 . 7) (370 . 13) (100 . "AcDbLine") (10 12286.9541628959
2417.0439705882 0.0) (11 12286.9541628959 2398.1900452489 0.0))
((0 . "LINE") (100 . "AcDbEntity") (8 . "MASONRY") (62 . 7) (370 . 13) (100 . "AcDbLine") (10 12281.2966742081
3141.0258710407 0.0) (11 12281.2966742081 3152.3380882353 0.0))
((0 . "LINE") (100 . "AcDbEntity") (8 . "MASONRY") (62 . 7) (370 . 13) (100 . "AcDbLine") (10 12458.5223303167
1749.4753959276 0.0) (11 12311.4635067873 1749.4753959276 0.0))
((0 . "LINE") (100 . "AcDbEntity") (8 . "MASONRY") (62 . 7) (370 . 13) (100 . "AcDbLine") (10 12311.4635067873
1749.4753959276 0.0) (11 12281.2966742081 1749.4753959276 0.0))
((0 . "LINE") (100 . "AcDbEntity") (8 . "MASONRY") (62 . 7) (370 . 13) (100 . "AcDbLine") (10 12285.0678733032
1668.5520361991 0.0) (11 12296.3800904977 1668.5520361991 0.0))
((0 . "LINE") (100 . "AcDbEntity") (8 . "MASONRY") (62 . 7) (370 . 13) (100 . "AcDbLine") (10 12285.0678733032
818.2494570136 0.0) (11 12285.0678733032 788.0853846154 0.0))
((0 . "LINE") (100 . "AcDbEntity") (8 . "MASONRY") (62 . 7) (370 . 13) (100 . "AcDbLine") (10 12526.3956334842
788.0853846154 0.0) (11 12412.9310067873 788.0853846154 0.0))
((0 . "LINE") (100 . "AcDbEntity") (8 . "MASONRY") (62 . 7) (370 . 13) (100 . "AcDbLine") (10 12341.8887556561
788.0853846154 0.0) (11 12285.0678733032 788.0853846154 0.0))
((0 . "LINE") (100 . "AcDbEntity") (8 . "MASONRY") (62 . 7) (370 . 13) (100 . "AcDbLine") (10 12492.4589819005
3103.3187104072 0.0) (11 12288.8390723982 3103.3187104072 0.0))
((0 . "LINE") (100 . "AcDbEntity") (8 . "MASONRY") (62 . 7) (370 . 13) (100 . "AcDbLine") (10 12288.8390723982
2473.6050565611 0.0) (11 12288.8390723982 2462.2928393665 0.0))
((0 . "LINE") (100 . "AcDbEntity") (8 . "MASONRY") (62 . 7) (370 . 13) (100 . "AcDbLine") (10 12296.3800904977
1662.8959276018 0.0) (11 12296.3800904977 1668.5520361991 0.0))
((0 . "LINE") (100 . "AcDbEntity") (8 . "MASONRY") (62 . 7) (370 . 13) (100 . "AcDbLine") (10 12296.3800904977
1708.1447963801 0.0) (11 12296.3800904977 1668.5520361991 0.0))
((0 . "LINE") (100 . "AcDbEntity") (8 . "MASONRY") (62 . 7) (370 . 13) (100 . "AcDbLine") (10 12513.1971266968
2824.2837895928 0.0) (11 12296.3800904977 2824.2837895928 0.0))
((0 . "LINE") (100 . "AcDbEntity") (8 . "MASONRY") (62 . 7) (370 . 13) (100 . "AcDbLine") (10 12303.9211085973
726.4723303167 0.0) (11 12322.7715837104 726.4723303167 0.0))
((0 . "LINE") (100 . "AcDbEntity") (8 . "MASONRY") (62 . 7) (370 . 13) (100 . "AcDbLine") (10 12322.7715837104
726.4723303167 0.0) (11 12322.7715837104 746.6063348416 0.0))
((0 . "LINE") (100 . "AcDbEntity") (8 . "MASONRY") (62 . 7) (370 . 13) (100 . "AcDbLine") (10 12307.6923076923
1242.4589819005 0.0) (11 12307.6923076923 1217.949638009 0.0))
((0 . "LINE") (100 . "AcDbEntity") (8 . "MASONRY") (62 . 7) (370 . 13) (100 . "AcDbLine") (10 12714.9321266968
1242.4589819005 0.0) (11 12594.2689366516 1242.4589819005 0.0))
((0 . "LINE") (100 . "AcDbEntity") (8 . "MASONRY") (62 . 7) (370 . 13) (100 . "AcDbLine") (10 12594.2689366516
1242.4589819005 0.0) (11 12564.1021040724 1242.4589819005 0.0))
((0 . "LINE") (100 . "AcDbEntity") (8 . "MASONRY") (62 . 7) (370 . 13) (100 . "AcDbLine") (10 12564.1021040724
1242.4589819005 0.0) (11 12477.3755656109 1242.4589819005 0.0))
((0 . "LINE") (100 . "AcDbEntity") (8 . "MASONRY") (62 . 7) (370 . 13) (100 . "AcDbLine") (10 12477.3755656109
1242.4589819005 0.0) (11 12307.6923076923 1242.4589819005 0.0))
((0 . "LINE") (100 . "AcDbEntity") (8 . "MASONRY") (62 . 7) (370 . 13) (100 . "AcDbLine") (10 12718.7033257919
2300.1505995475 0.0) (11 12311.4635067873 2300.1505995475 0.0))
((0 . "LINE") (100 . "AcDbEntity") (8 . "MASONRY") (62 . 7) (370 . 13) (100 . "AcDbLine") (10 12428.3554977376
1282.050361991 0.0) (11 12394.4188461538 1282.050361991 0.0))
((0 . "LINE") (100 . "AcDbEntity") (8 . "MASONRY") (62 . 7) (370 . 13) (100 . "AcDbLine") (10 12394.4188461538
1282.050361991 0.0) (11 12311.4635067873 1282.050361991 0.0))
((0 . "LINE") (100 . "AcDbEntity") (8 . "MASONRY") (62 . 7) (370 . 13) (100 . "AcDbLine") (10 12319.0045248869
3389.8946493213 0.0) (11 12337.857760181 3389.8946493213 0.0))
((0 . "LINE") (100 . "AcDbEntity") (8 . "MASONRY") (62 . 7) (370 . 13) (100 . "AcDbLine") (10 12319.0045248869
3389.8946493213 0.0) (11 12319.0045248869 3337.1040723982 0.0))
((0 . "LINE") (100 . "AcDbEntity") (8 . "MASONRY") (62 . 7) (370 . 13) (100 . "AcDbLine") (10 12319.0045248869
3389.8946493213 0.0) (11 12319.0045248869 3423.831300905 0.0))
((0 . "LINE") (100 . "AcDbEntity") (8 . "MASONRY") (62 . 7) (370 . 13) (100 . "AcDbLine") (10 12317.1182352941
1180.2404072398 0.0) (11 12317.1182352941 1116.1396832579 0.0))
((0 . "LINE") (100 . "AcDbEntity") (8 . "MASONRY") (62 . 7) (370 . 13) (100 . "AcDbLine") (10 12317.1182352941
1180.2404072398 0.0) (11 12533.9366515837 1180.2404072398 0.0))
((0 . "LINE") (100 . "AcDbEntity") (8 . "MASONRY") (62 . 7) (370 . 13) (100 . "AcDbLine") (10 12334.0879411765
1033.1815837104 0.0) (11 12317.7203054299 1033.1815837104 0.0))
((0 . "LINE") (100 . "AcDbEntity") (8 . "MASONRY") (62 . 7) (370 . 13) (100 . "AcDbLine") (10 12598.0387556561
1082.054581448 0.0) (11 12345.400158371 1082.054581448 0.0))
((0 . "LINE") (100 . "AcDbEntity") (8 . "MASONRY") (62 . 7) (370 . 13) (100 . "AcDbLine") (10 12345.400158371
1082.054581448 0.0) (11 12317.7203054299 1082.054581448 0.0))
((0 . "LINE") (100 . "AcDbEntity") (8 . "MASONRY") (62 . 7) (370 . 13) (100 . "AcDbLine") (10 12317.7203054299
1082.054581448 0.0) (11 12317.7203054299 1033.1815837104 0.0))
((0 . "LINE") (100 . "AcDbEntity") (8 . "MASONRY") (62 . 7) (370 . 13) (100 . "AcDbLine") (10 12319.0045248869
3306.9379298643 0.0) (11 12319.0045248869 3265.460260181 0.0))
((0 . "LINE") (100 . "AcDbEntity") (8 . "MASONRY") (62 . 7) (370 . 13) (100 . "AcDbLine") (10 12541.4776696833
3265.460260181 0.0) (11 12319.0045248869 3265.460260181 0.0))
((0 . "LINE") (100 . "AcDbEntity") (8 . "MASONRY") (62 . 7) (370 . 13) (100 . "AcDbLine") (10 12319.0045248869
678.7330316742 0.0) (11 12319.0045248869 656.1085972851 0.0))
((0 . "LINE") (100 . "AcDbEntity") (8 . "MASONRY") (62 . 7) (370 . 13) (100 . "AcDbLine") (10 12322.7757239819
2790.3471380091 0.0) (11 12322.7757239819 2756.4097963801 0.0))
((0 . "LINE") (100 . "AcDbEntity") (8 . "MASONRY") (62 . 7) (370 . 13) (100 . "AcDbLine") (10 12426.4705882353
2756.4097963801 0.0) (11 12322.7757239819 2756.4097963801 0.0))
((0 . "LINE") (100 . "AcDbEntity") (8 . "MASONRY") (62 . 7) (370 . 13) (100 . "AcDbLine") (10 12324.6606334842
2505.5815384615 0.0) (11 12324.6606334842 2556.5610859729 0.0))
((0 . "LINE") (100 . "AcDbEntity") (8 . "MASONRY") (62 . 7) (370 . 13) (100 . "AcDbLine") (10 12575.414321267
2505.5815384615 0.0) (11 12533.9366515837 2505.5815384615 0.0))
((0 . "LINE") (100 . "AcDbEntity") (8 . "MASONRY") (62 . 7) (370 . 13) (100 . "AcDbLine") (10 12533.9366515837
2505.5815384615 0.0) (11 12324.6606334842 2505.5815384615 0.0))
((0 . "LINE") (100 . "AcDbEntity") (8 . "MASONRY") (62 . 7) (370 . 13) (100 . "AcDbLine") (10 12326.5455429864
584.4654751131 0.0) (11 12326.5455429864 550.5288235294 0.0))
((0 . "LINE") (100 . "AcDbEntity") (8 . "MASONRY") (62 . 7) (370 . 13) (100 . "AcDbLine") (10 12332.2030316742
2209.6528619909 0.0) (11 12332.2030316742 2164.4039932127 0.0))
((0 . "LINE") (100 . "AcDbEntity") (8 . "MASONRY") (62 . 7) (370 . 13) (100 . "AcDbLine") (10 12535.7483710407
3374.8112330317 0.0) (11 12535.7483710407 3419.3841628959 0.0))
((0 . "LINE") (100 . "AcDbEntity") (8 . "MASONRY") (62 . 7) (370 . 13) (100 . "AcDbLine") (10 12535.7483710407
3419.3841628959 0.0) (11 12356.7123755656 3419.3841628959 0.0))
((0 . "LINE") (100 . "AcDbEntity") (8 . "MASONRY") (62 . 7) (370 . 13) (100 . "AcDbLine") (10 12356.7123755656
2113.4997058824 0.0) (11 12368.0245927602 2113.4997058824 0.0))
((0 . "LINE") (100 . "AcDbEntity") (8 . "MASONRY") (62 . 7) (370 . 13) (100 . "AcDbLine") (10 12360.4821945701
1029.4117647059 0.0) (11 12390.6490271493 1029.4117647059 0.0))
((0 . "LINE") (100 . "AcDbEntity") (8 . "MASONRY") (62 . 7) (370 . 13) (100 . "AcDbLine") (10 12368.0245927602
1393.2876244344 0.0) (11 12375.5656108597 1393.2876244344 0.0))
((0 . "LINE") (100 . "AcDbEntity") (8 . "MASONRY") (62 . 7) (370 . 13) (100 . "AcDbLine") (10 12383.1066289593
2043.7408031674 0.0) (11 12511.3122171946 2043.7408031674 0.0))
((0 . "LINE") (100 . "AcDbEntity") (8 . "MASONRY") (62 . 7) (370 . 13) (100 . "AcDbLine") (10 12417.043280543
2895.92760181 0.0) (11 12541.4776696833 2895.92760181 0.0))
((0 . "LINE") (100 . "AcDbEntity") (8 . "MASONRY") (62 . 7) (370 . 13) (100 . "AcDbLine") (10 12432.1266968326
2088.9896719457 0.0) (11 12420.814479638 2088.9896719457 0.0))
((0 . "LINE") (100 . "AcDbEntity") (8 . "MASONRY") (62 . 7) (370 . 13) (100 . "AcDbLine") (10 12420.814479638
2130.467341629 0.0) (11 12420.814479638 2088.9896719457 0.0))
((0 . "LINE") (100 . "AcDbEntity") (8 . "MASONRY") (62 . 7) (370 . 13) (100 . "AcDbLine") (10 12417.043280543
1817.4971493213 0.0) (11 12469.8345475113 1817.4971493213 0.0))
((0 . "LINE") (100 . "AcDbEntity") (8 . "MASONRY") (62 . 7) (370 . 13) (100 . "AcDbLine") (10 12420.814479638
1474.3580542986 0.0) (11 12420.814479638 1504.5248868778 0.0))
((0 . "LINE") (100 . "AcDbEntity") (8 . "MASONRY") (62 . 7) (370 . 13) (100 . "AcDbLine") (10 12426.4705882353
2756.4097963801 0.0) (11 12426.4705882353 2711.1616176471 0.0))
((0 . "LINE") (100 . "AcDbEntity") (8 . "MASONRY") (62 . 7) (370 . 13) (100 . "AcDbLine") (10 12426.4705882353
2756.4097963801 0.0) (11 12533.9366515837 2756.4097963801 0.0))
((0 . "LINE") (100 . "AcDbEntity") (8 . "MASONRY") (62 . 7) (370 . 13) (100 . "AcDbLine") (10 12628.2042081448
2209.6528619909 0.0) (11 12424.585678733 2209.6528619909 0.0))
((0 . "LINE") (100 . "AcDbEntity") (8 . "MASONRY") (62 . 7) (370 . 13) (100 . "AcDbLine") (10 12432.1266968326
1530.9191402715 0.0) (11 12426.4705882353 1530.9191402715 0.0))
((0 . "LINE") (100 . "AcDbEntity") (8 . "MASONRY") (62 . 7) (370 . 13) (100 . "AcDbLine") (10 12426.4705882353
1530.9191402715 0.0) (11 12426.4705882353 1561.0859728507 0.0))
((0 . "LINE") (100 . "AcDbEntity") (8 . "MASONRY") (62 . 7) (370 . 13) (100 . "AcDbLine") (10 12428.3554977376
2630.0904977376 0.0) (11 12428.3554977376 2662.1415497738 0.0))
((0 . "LINE") (100 . "AcDbEntity") (8 . "MASONRY") (62 . 7) (370 . 13) (100 . "AcDbLine") (10 12428.3554977376
2584.8416289593 0.0) (11 12507.5410180995 2584.8416289593 0.0))
((0 . "LINE") (100 . "AcDbEntity") (8 . "MASONRY") (62 . 7) (370 . 13) (100 . "AcDbLine") (10 12428.3554977376
2584.8416289593 0.0) (11 12428.3554977376 2630.0904977376 0.0))
((0 . "LINE") (100 . "AcDbEntity") (8 . "MASONRY") (62 . 7) (370 . 13) (100 . "AcDbLine") (10 12435.8978959276
1034.4395701357 0.0) (11 12428.3554977376 1034.4395701357 0.0))
((0 . "LINE") (100 . "AcDbEntity") (8 . "MASONRY") (62 . 7) (370 . 13) (100 . "AcDbLine") (10 12484.9165837104
737.1790271493 0.0) (11 12469.8345475113 737.1790271493 0.0))
((0 . "LINE") (100 . "AcDbEntity") (8 . "MASONRY") (62 . 7) (370 . 13) (100 . "AcDbLine") (10 12428.3554977376
2630.0904977376 0.0) (11 12533.9366515837 2630.0904977376 0.0))
((0 . "LINE") (100 . "AcDbEntity") (8 . "MASONRY") (62 . 7) (370 . 13) (100 . "AcDbLine") (10 12434.0129864253
1907.9941968326 0.0) (11 12628.2055882353 1907.9941968326 0.0))
((0 . "LINE") (100 . "AcDbEntity") (8 . "MASONRY") (62 . 7) (370 . 13) (100 . "AcDbLine") (10 12628.2055882353
1907.9941968326 0.0) (11 12628.2055882353 1926.8474321267 0.0))
((0 . "LINE") (100 . "AcDbEntity") (8 . "MASONRY") (62 . 7) (370 . 13) (100 . "AcDbLine") (10 12434.0129864253
1923.0769230769 0.0) (11 12434.0129864253 1907.9941968326 0.0))
((0 . "LINE") (100 . "AcDbEntity") (8 . "MASONRY") (62 . 7) (370 . 13) (100 . "AcDbLine") (10 12435.8978959276
1874.0575452489 0.0) (11 12435.8978959276 1862.7453280543 0.0))
((0 . "LINE") (100 . "AcDbEntity") (8 . "MASONRY") (62 . 7) (370 . 13) (100 . "AcDbLine") (10 12435.8978959276
997.4373529412 0.0) (11 12639.5178054299 997.4373529412 0.0))
((0 . "LINE") (100 . "AcDbEntity") (8 . "MASONRY") (62 . 7) (370 . 13) (100 . "AcDbLine") (10 12639.5178054299
997.4373529412 0.0) (11 12639.5178054299 1052.036199095 0.0))
((0 . "LINE") (100 . "AcDbEntity") (8 . "MASONRY") (62 . 7) (370 . 13) (100 . "AcDbLine") (10 12466.0633484163
2088.9896719457 0.0) (11 12560.3322850679 2088.9896719457 0.0))
((0 . "LINE") (100 . "AcDbEntity") (8 . "MASONRY") (62 . 7) (370 . 13) (100 . "AcDbLine") (10 12522.6244343891
1596.9075339367 0.0) (11 12469.8345475113 1596.9075339367 0.0))
((0 . "LINE") (100 . "AcDbEntity") (8 . "MASONRY") (62 . 7) (370 . 13) (100 . "AcDbLine") (10 12469.8345475113
1568.6269909502 0.0) (11 12865.7621493213 1568.6269909502 0.0))
((0 . "LINE") (100 . "AcDbEntity") (8 . "MASONRY") (62 . 7) (370 . 13) (100 . "AcDbLine") (10 12571.6445022624
1817.4971493213 0.0) (11 12481.1467647059 1817.4971493213 0.0))
((0 . "LINE") (100 . "AcDbEntity") (8 . "MASONRY") (62 . 7) (370 . 13) (100 . "AcDbLine") (10 12492.45760181
1693.062760181 0.0) (11 12492.45760181 1644.0413122172 0.0))
((0 . "LINE") (100 . "AcDbEntity") (8 . "MASONRY") (62 . 7) (370 . 13) (100 . "AcDbLine") (10 12488.6877828054
1749.6238461538 0.0) (11 12503.771199095 1749.6238461538 0.0))
((0 . "LINE") (100 . "AcDbEntity") (8 . "MASONRY") (62 . 7) (370 . 13) (100 . "AcDbLine") (10 12549.0200678733
708.0533823529 0.0) (11 12501.0425678733 708.0533823529 0.0))
((0 . "LINE") (100 . "AcDbEntity") (8 . "MASONRY") (62 . 7) (370 . 13) (100 . "AcDbLine") (10 12503.771199095
1760.9360633484 0.0) (11 12503.771199095 1749.6238461538 0.0))
((0 . "LINE") (100 . "AcDbEntity") (8 . "MASONRY") (62 . 7) (370 . 13) (100 . "AcDbLine") (10 12503.771199095
1749.6238461538 0.0) (11 12530.1654524887 1749.6238461538 0.0))
((0 . "LINE") (100 . "AcDbEntity") (8 . "MASONRY") (62 . 7) (370 . 13) (100 . "AcDbLine") (10 12513.1971266968
2858.2204411765 0.0) (11 12513.1971266968 2824.2837895928 0.0))
((0 . "LINE") (100 . "AcDbEntity") (8 . "MASONRY") (62 . 7) (370 . 13) (100 . "AcDbLine") (10 12513.1971266968
2824.2837895928 0.0) (11 12541.4776696833 2824.2837895928 0.0))
((0 . "LINE") (100 . "AcDbEntity") (8 . "MASONRY") (62 . 7) (370 . 13) (100 . "AcDbLine") (10 12590.4977375566
1042.6088914027 0.0) (11 12515.0834162896 1042.6088914027 0.0))
((0 . "LINE") (100 . "AcDbEntity") (8 . "MASONRY") (62 . 7) (370 . 13) (100 . "AcDbLine") (10 12518.8532352941
2582.9560294118 0.0) (11 12537.7078506787 2582.9560294118 0.0))
((0 . "LINE") (100 . "AcDbEntity") (8 . "MASONRY") (62 . 7) (370 . 13) (100 . "AcDbLine") (10 12528.2805429864
859.7285067873 0.0) (11 12528.2805429864 871.0407239819 0.0))
((0 . "LINE") (100 . "AcDbEntity") (8 . "MASONRY") (62 . 7) (370 . 13) (100 . "AcDbLine") (10 12526.3956334842
788.0853846154 0.0) (11 12526.3956334842 844.6464705882 0.0))
((0 . "LINE") (100 . "AcDbEntity") (8 . "MASONRY") (62 . 7) (370 . 13) (100 . "AcDbLine") (10 12526.3956334842
788.0853846154 0.0) (11 12537.7078506787 788.0853846154 0.0))
((0 . "LINE") (100 . "AcDbEntity") (8 . "MASONRY") (62 . 7) (370 . 13) (100 . "AcDbLine") (10 12530.1654524887
904.9773755656 0.0) (11 12541.4776696833 904.9773755656 0.0))
((0 . "LINE") (100 . "AcDbEntity") (8 . "MASONRY") (62 . 7) (370 . 13) (100 . "AcDbLine") (10 12533.9366515837
3171.1913235294 0.0) (11 12533.9366515837 3190.0452488688 0.0))
((0 . "LINE") (100 . "AcDbEntity") (8 . "MASONRY") (62 . 7) (370 . 13) (100 . "AcDbLine") (10 12533.9366515837
3190.0452488688 0.0) (11 12533.9366515837 3220.2113914027 0.0))
((0 . "LINE") (100 . "AcDbEntity") (8 . "MASONRY") (62 . 7) (370 . 13) (100 . "AcDbLine") (10 12537.7078506787
3118.4014366516 0.0) (11 12537.7078506787 3133.4841628959 0.0))
((0 . "LINE") (100 . "AcDbEntity") (8 . "MASONRY") (62 . 7) (370 . 13) (100 . "AcDbLine") (10 12539.592760181
2944.946979638 0.0) (11 12539.592760181 2993.9670475113 0.0))
((0 . "LINE") (100 . "AcDbEntity") (8 . "MASONRY") (62 . 7) (370 . 13) (100 . "AcDbLine") (10 12537.7078506787
2533.9366515837 0.0) (11 12537.7078506787 2526.3949434389 0.0))
((0 . "LINE") (100 . "AcDbEntity") (8 . "MASONRY") (62 . 7) (370 . 13) (100 . "AcDbLine") (10 12552.7898868778
2254.9017307692 0.0) (11 12537.7078506787 2254.9017307692 0.0))
((0 . "LINE") (100 . "AcDbEntity") (8 . "MASONRY") (62 . 7) (370 . 13) (100 . "AcDbLine") (10 12541.4776696833
3310.7091289593 0.0) (11 12541.4776696833 3359.7285067873 0.0))
((0 . "LINE") (100 . "AcDbEntity") (8 . "MASONRY") (62 . 7) (370 . 13) (100 . "AcDbLine") (10 12549.0200678733
1762.1395022624 0.0) (11 12843.1377149321 1762.1395022624 0.0))
((0 . "LINE") (100 . "AcDbEntity") (8 . "MASONRY") (62 . 7) (370 . 13) (100 . "AcDbLine") (10 12843.1377149321
1762.1395022624 0.0) (11 12858.2197511312 1762.1395022624 0.0))
((0 . "LINE") (100 . "AcDbEntity") (8 . "MASONRY") (62 . 7) (370 . 13) (100 . "AcDbLine") (10 12549.0200678733
1598.8704638009 0.0) (11 12726.2415837104 1598.8704638009 0.0))
((0 . "LINE") (100 . "AcDbEntity") (8 . "MASONRY") (62 . 7) (370 . 13) (100 . "AcDbLine") (10 12726.2415837104
1598.8704638009 0.0) (11 12726.2415837104 1632.7290950226 0.0))
((0 . "LINE") (100 . "AcDbEntity") (8 . "MASONRY") (62 . 7) (370 . 13) (100 . "AcDbLine") (10 12552.7898868778
1184.0129864253 0.0) (11 12586.7265384615 1184.0129864253 0.0))
((0 . "LINE") (100 . "AcDbEntity") (8 . "MASONRY") (62 . 7) (370 . 13) (100 . "AcDbLine") (10 12564.1021040724
2043.7408031674 0.0) (11 12556.5610859729 2043.7408031674 0.0))
((0 . "LINE") (100 . "AcDbEntity") (8 . "MASONRY") (62 . 7) (370 . 13) (100 . "AcDbLine") (10 12560.3322850679
2088.9896719457 0.0) (11 12560.3322850679 2070.1357466063 0.0))
((0 . "LINE") (100 . "AcDbEntity") (8 . "MASONRY") (62 . 7) (370 . 13) (100 . "AcDbLine") (10 12726.2443438914
2111.6141063348 0.0) (11 12726.2443438914 2088.9896719457 0.0))
((0 . "LINE") (100 . "AcDbEntity") (8 . "MASONRY") (62 . 7) (370 . 13) (100 . "AcDbLine") (10 12726.2443438914
2088.9896719457 0.0) (11 12560.3322850679 2088.9896719457 0.0))
((0 . "LINE") (100 . "AcDbEntity") (8 . "MASONRY") (62 . 7) (370 . 13) (100 . "AcDbLine") (10 12567.8733031674
2383.1073190045 0.0) (11 12730.0155429864 2383.1073190045 0.0))
((0 . "LINE") (100 . "AcDbEntity") (8 . "MASONRY") (62 . 7) (370 . 13) (100 . "AcDbLine") (10 12579.185520362
1436.6515837104 0.0) (11 12579.185520362 1447.963800905 0.0))
((0 . "LINE") (100 . "AcDbEntity") (8 . "MASONRY") (62 . 7) (370 . 13) (100 . "AcDbLine") (10 12971.3419230769
1436.6515837104 0.0) (11 12914.7808371041 1436.6515837104 0.0))
((0 . "LINE") (100 . "AcDbEntity") (8 . "MASONRY") (62 . 7) (370 . 13) (100 . "AcDbLine") (10 12914.7808371041
1436.6515837104 0.0) (11 12892.1508823529 1436.6515837104 0.0))
((0 . "LINE") (100 . "AcDbEntity") (8 . "MASONRY") (62 . 7) (370 . 13) (100 . "AcDbLine") (10 12892.1508823529
1436.6515837104 0.0) (11 12654.599841629 1436.6515837104 0.0))
((0 . "LINE") (100 . "AcDbEntity") (8 . "MASONRY") (62 . 7) (370 . 13) (100 . "AcDbLine") (10 12654.599841629
1436.6515837104 0.0) (11 12605.5811538462 1436.6515837104 0.0))
((0 . "LINE") (100 . "AcDbEntity") (8 . "MASONRY") (62 . 7) (370 . 13) (100 . "AcDbLine") (10 12605.5811538462
1436.6515837104 0.0) (11 12579.185520362 1436.6515837104 0.0))
((0 . "LINE") (100 . "AcDbEntity") (8 . "MASONRY") (62 . 7) (370 . 13) (100 . "AcDbLine") (10 12582.956719457
1134.9915384615 0.0) (11 12820.513280543 1134.9915384615 0.0))
((0 . "LINE") (100 . "AcDbEntity") (8 . "MASONRY") (62 . 7) (370 . 13) (100 . "AcDbLine") (10 12588.6114479638
1523.3795022624 0.0) (11 12588.6114479638 1534.691719457 0.0))
((0 . "LINE") (100 . "AcDbEntity") (8 . "MASONRY") (62 . 7) (370 . 13) (100 . "AcDbLine") (10 12590.4977375566
2039.9696040724 0.0) (11 12626.320678733 2039.9696040724 0.0))
((0 . "LINE") (100 . "AcDbEntity") (8 . "MASONRY") (62 . 7) (370 . 13) (100 . "AcDbLine") (10 12683.7102941176
833.5600339367 0.0) (11 12683.7102941176 723.9819004525 0.0))
((0 . "LINE") (100 . "AcDbEntity") (8 . "MASONRY") (62 . 7) (370 . 13) (100 . "AcDbLine") (10 12683.7102941176
723.9819004525 0.0) (11 12683.7102941176 689.0582918552 0.0))
((0 . "LINE") (100 . "AcDbEntity") (8 . "MASONRY") (62 . 7) (370 . 13) (100 . "AcDbLine") (10 12590.4977375566
857.4660633484 0.0) (11 12590.4977375566 863.4983257919 0.0))
((0 . "LINE") (100 . "AcDbEntity") (8 . "MASONRY") (62 . 7) (370 . 13) (100 . "AcDbLine") (10 12590.4977375566
868.9825113122 0.0) (11 12590.4977375566 863.4983257919 0.0))
((0 . "LINE") (100 . "AcDbEntity") (8 . "MASONRY") (62 . 7) (370 . 13) (100 . "AcDbLine") (10 12624.4343891403
1862.7453280543 0.0) (11 12616.8933710407 1862.7453280543 0.0))
((0 . "LINE") (100 . "AcDbEntity") (8 . "MASONRY") (62 . 7) (370 . 13) (100 . "AcDbLine") (10 13026.0180995475
1817.4971493213 0.0) (11 12624.4343891403 1817.4971493213 0.0))
((0 . "LINE") (100 . "AcDbEntity") (8 . "MASONRY") (62 . 7) (370 . 13) (100 . "AcDbLine") (10 12624.4343891403
1817.4971493213 0.0) (11 12624.4343891403 1798.6425339367 0.0))
((0 . "LINE") (100 . "AcDbEntity") (8 . "MASONRY") (62 . 7) (370 . 13) (100 . "AcDbLine") (10 12679.1105656109
2209.6528619909 0.0) (11 12628.2042081448 2209.6528619909 0.0))
((0 . "LINE") (100 . "AcDbEntity") (8 . "MASONRY") (62 . 7) (370 . 13) (100 . "AcDbLine") (10 12628.2042081448
2209.6528619909 0.0) (11 12628.2042081448 2243.5895135747 0.0))
((0 . "LINE") (100 . "AcDbEntity") (8 . "MASONRY") (62 . 7) (370 . 13) (100 . "AcDbLine") (10 12626.320678733
2039.9696040724 0.0) (11 12626.320678733 1975.8675 0.0))
((0 . "LINE") (100 . "AcDbEntity") (8 . "MASONRY") (62 . 7) (370 . 13) (100 . "AcDbLine") (10 12809.2010633484
2039.9696040724 0.0) (11 12626.320678733 2039.9696040724 0.0))
((0 . "LINE") (100 . "AcDbEntity") (8 . "MASONRY") (62 . 7) (370 . 13) (100 . "AcDbLine") (10 12677.2242760181
1184.0129864253 0.0) (11 12624.4343891403 1184.0129864253 0.0))
((0 . "LINE") (100 . "AcDbEntity") (8 . "MASONRY") (62 . 7) (370 . 13) (100 . "AcDbLine") (10 12628.2055882353
1941.9308484163 0.0) (11 12628.2055882353 1926.8474321267 0.0))
((0 . "LINE") (100 . "AcDbEntity") (8 . "MASONRY") (62 . 7) (370 . 13) (100 . "AcDbLine") (10 12839.3665158371
1926.8474321267 0.0) (11 12628.2055882353 1926.8474321267 0.0))
((0 . "LINE") (100 . "AcDbEntity") (8 . "MASONRY") (62 . 7) (370 . 13) (100 . "AcDbLine") (10 12631.9754072398
1263.1985067873 0.0) (11 12662.142239819 1263.1985067873 0.0))
((0 . "LINE") (100 . "AcDbEntity") (8 . "MASONRY") (62 . 7) (370 . 13) (100 . "AcDbLine") (10 12639.5178054299
1052.036199095 0.0) (11 12639.5178054299 1059.5785972851 0.0))
((0 . "LINE") (100 . "AcDbEntity") (8 . "MASONRY") (62 . 7) (370 . 13) (100 . "AcDbLine") (10 12639.5178054299
1052.036199095 0.0) (11 12807.3161538462 1052.036199095 0.0))
((0 . "LINE") (100 . "AcDbEntity") (8 . "MASONRY") (62 . 7) (370 . 13) (100 . "AcDbLine") (10 12750.83239819
912.5197737557 0.0) (11 12643.2876244344 912.5197737557 0.0))
((0 . "LINE") (100 . "AcDbEntity") (8 . "MASONRY") (62 . 7) (370 . 13) (100 . "AcDbLine") (10 12673.4544570136
3438.9140271493 0.0) (11 12665.9120588235 3438.9140271493 0.0))
((0 . "LINE") (100 . "AcDbEntity") (8 . "MASONRY") (62 . 7) (370 . 13) (100 . "AcDbLine") (10 12679.1105656109
2209.6528619909 0.0) (11 12737.556561086 2209.6528619909 0.0))
((0 . "LINE") (100 . "AcDbEntity") (8 . "MASONRY") (62 . 7) (370 . 13) (100 . "AcDbLine") (10 12737.556561086
2209.6528619909 0.0) (11 12895.92760181 2209.6528619909 0.0))
((0 . "LINE") (100 . "AcDbEntity") (8 . "MASONRY") (62 . 7) (370 . 13) (100 . "AcDbLine") (10 12679.1105656109
2209.6528619909 0.0) (11 12679.1105656109 2250.976561086 0.0))
((0 . "LINE") (100 . "AcDbEntity") (8 . "MASONRY") (62 . 7) (370 . 13) (100 . "AcDbLine") (10 12679.1105656109
2250.976561086 0.0) (11 12771.4932126697 2250.976561086 0.0))
((0 . "LINE") (100 . "AcDbEntity") (8 . "MASONRY") (62 . 7) (370 . 13) (100 . "AcDbLine") (10 12771.4932126697
2250.976561086 0.0) (11 12907.394479638 2250.976561086 0.0))
((0 . "LINE") (100 . "AcDbEntity") (8 . "MASONRY") (62 . 7) (370 . 13) (100 . "AcDbLine") (10 12692.3076923077
1423.4544570136 0.0) (11 12673.4544570136 1423.4544570136 0.0))
((0 . "LINE") (100 . "AcDbEntity") (8 . "MASONRY") (62 . 7) (370 . 13) (100 . "AcDbLine") (10 12673.4544570136
880.4680316742 0.0) (11 12707.3911085973 880.4680316742 0.0))
((0 . "LINE") (100 . "AcDbEntity") (8 . "MASONRY") (62 . 7) (370 . 13) (100 . "AcDbLine") (10 12726.2443438914
995.4751131222 0.0) (11 12688.5364932127 995.4751131222 0.0))
((0 . "LINE") (100 . "AcDbEntity") (8 . "MASONRY") (62 . 7) (370 . 13) (100 . "AcDbLine") (10 12707.3911085973
1415.9873190045 0.0) (11 12724.3594343891 1415.9873190045 0.0))
((0 . "LINE") (100 . "AcDbEntity") (8 . "MASONRY") (62 . 7) (370 . 13) (100 . "AcDbLine") (10 12714.9321266968
1242.4589819005 0.0) (11 12714.9321266968 1300.9049773756 0.0))
((0 . "LINE") (100 . "AcDbEntity") (8 . "MASONRY") (62 . 7) (370 . 13) (100 . "AcDbLine") (10 12707.3911085973
825.7918552036 0.0) (11 12824.2830995475 825.7918552036 0.0))
((0 . "LINE") (100 . "AcDbEntity") (8 . "MASONRY") (62 . 7) (370 . 13) (100 . "AcDbLine") (10 13114.6309276018
1104.8274660633 0.0) (11 12874.5003959276 1104.8274660633 0.0))
((0 . "LINE") (100 . "AcDbEntity") (8 . "MASONRY") (62 . 7) (370 . 13) (100 . "AcDbLine") (10 12874.5003959276
1104.8274660633 0.0) (11 12874.5003959276 1131.221719457 0.0))
((0 . "LINE") (100 . "AcDbEntity") (8 . "MASONRY") (62 . 7) (370 . 13) (100 . "AcDbLine") (10 12874.5003959276
1131.221719457 0.0) (11 12874.5003959276 1187.1807352941 0.0))
((0 . "LINE") (100 . "AcDbEntity") (8 . "MASONRY") (62 . 7) (370 . 13) (100 . "AcDbLine") (10 12874.5003959276
1187.1807352941 0.0) (11 12711.1609276018 1187.1807352941 0.0))
((0 . "LINE") (100 . "AcDbEntity") (8 . "MASONRY") (62 . 7) (370 . 13) (100 . "AcDbLine") (10 12724.3594343891
1387.6328959276 0.0) (11 12724.3594343891 1415.9873190045 0.0))
((0 . "LINE") (100 . "AcDbEntity") (8 . "MASONRY") (62 . 7) (370 . 13) (100 . "AcDbLine") (10 13088.2352941176
1344.2689366516 0.0) (11 12718.7033257919 1344.2689366516 0.0))
((0 . "LINE") (100 . "AcDbEntity") (8 . "MASONRY") (62 . 7) (370 . 13) (100 . "AcDbLine") (10 12718.7033257919
1344.2689366516 0.0) (11 12718.7033257919 1331.0718099548 0.0))
((0 . "LINE") (100 . "AcDbEntity") (8 . "MASONRY") (62 . 7) (370 . 13) (100 . "AcDbLine") (10 12726.2443438914
2111.6141063348 0.0) (11 12726.2443438914 2130.467341629 0.0))
((0 . "LINE") (100 . "AcDbEntity") (8 . "MASONRY") (62 . 7) (370 . 13) (100 . "AcDbLine") (10 13012.8209728507
2111.6141063348 0.0) (11 12726.2443438914 2111.6141063348 0.0))
((0 . "LINE") (100 . "AcDbEntity") (8 . "MASONRY") (62 . 7) (370 . 13) (100 . "AcDbLine") (10 12724.3594343891
1415.9873190045 0.0) (11 12839.3665158371 1415.9873190045 0.0))
((0 . "LINE") (100 . "AcDbEntity") (8 . "MASONRY") (62 . 7) (370 . 13) (100 . "AcDbLine") (10 12839.3665158371
1415.9873190045 0.0) (11 12858.2197511312 1415.9873190045 0.0))
((0 . "LINE") (100 . "AcDbEntity") (8 . "MASONRY") (62 . 7) (370 . 13) (100 . "AcDbLine") (10 12737.559321267
1711.9146153846 0.0) (11 12737.559321267 1681.8271832579 0.0))
((0 . "LINE") (100 . "AcDbEntity") (8 . "MASONRY") (62 . 7) (370 . 13) (100 . "AcDbLine") (10 12737.559321267
1681.8271832579 0.0) (11 12850.6787330317 1681.8271832579 0.0))
((0 . "LINE") (100 . "AcDbEntity") (8 . "MASONRY") (62 . 7) (370 . 13) (100 . "AcDbLine") (10 12756.4097963801
2496.2294909502 0.0) (11 12745.0975791855 2496.2294909502 0.0))
((0 . "LINE") (100 . "AcDbEntity") (8 . "MASONRY") (62 . 7) (370 . 13) (100 . "AcDbLine") (10 12786.5766289593
886.122760181 0.0) (11 12750.83239819 886.122760181 0.0))
((0 . "LINE") (100 . "AcDbEntity") (8 . "MASONRY") (62 . 7) (370 . 13) (100 . "AcDbLine") (10 12750.83239819
886.122760181 0.0) (11 12750.83239819 912.5197737557 0.0))
((0 . "LINE") (100 . "AcDbEntity") (8 . "MASONRY") (62 . 7) (370 . 13) (100 . "AcDbLine") (10 12774.662341629
969.0808597285 0.0) (11 12774.662341629 912.5197737557 0.0))
((0 . "LINE") (100 . "AcDbEntity") (8 . "MASONRY") (62 . 7) (370 . 13) (100 . "AcDbLine") (10 12774.662341629
912.5197737557 0.0) (11 12750.83239819 912.5197737557 0.0))
((0 . "LINE") (100 . "AcDbEntity") (8 . "MASONRY") (62 . 7) (370 . 13) (100 . "AcDbLine") (10 12752.6399773756
1263.1985067873 0.0) (11 12854.4499321267 1263.1985067873 0.0))
((0 . "LINE") (100 . "AcDbEntity") (8 . "MASONRY") (62 . 7) (370 . 13) (100 . "AcDbLine") (10 12756.4097963801
2379.3368099548 0.0) (11 12779.0342307692 2379.3368099548 0.0))
((0 . "LINE") (100 . "AcDbEntity") (8 . "MASONRY") (62 . 7) (370 . 13) (100 . "AcDbLine") (10 12756.4097963801
995.4751131222 0.0) (11 13029.787918552 995.4751131222 0.0))
((0 . "LINE") (100 . "AcDbEntity") (8 . "MASONRY") (62 . 7) (370 . 13) (100 . "AcDbLine") (10 12905.4860972851
711.8625565611 0.0) (11 12905.4860972851 796.9085520362 0.0))
((0 . "LINE") (100 . "AcDbEntity") (8 . "MASONRY") (62 . 7) (370 . 13) (100 . "AcDbLine") (10 12905.4860972851
796.9085520362 0.0) (11 12904.7296606335 796.9085520362 0.0))
((0 . "LINE") (100 . "AcDbEntity") (8 . "MASONRY") (62 . 7) (370 . 13) (100 . "AcDbLine") (10 12893.8523303167
796.9085520362 0.0) (11 12821.6939366516 796.9085520362 0.0))
((0 . "LINE") (100 . "AcDbEntity") (8 . "MASONRY") (62 . 7) (370 . 13) (100 . "AcDbLine") (10 12821.6939366516
796.9085520362 0.0) (11 12821.6939366516 702.2006674208 0.0))
((0 . "LINE") (100 . "AcDbEntity") (8 . "MASONRY") (62 . 7) (370 . 13) (100 . "AcDbLine") (10 12763.9521945701
2319.0045248869 0.0) (11 12763.9521945701 2345.3994683258 0.0))
((0 . "LINE") (100 . "AcDbEntity") (8 . "MASONRY") (62 . 7) (370 . 13) (100 . "AcDbLine") (10 12763.9521945701
2303.9217986425 0.0) (11 12763.9521945701 2319.0045248869 0.0))
((0 . "LINE") (100 . "AcDbEntity") (8 . "MASONRY") (62 . 7) (370 . 13) (100 . "AcDbLine") (10 12771.4932126697 2500 0.0)
(11 12914.7808371041 2500 0.0))
((0 . "LINE") (100 . "AcDbEntity") (8 . "MASONRY") (62 . 7) (370 . 13) (100 . "AcDbLine") (10 12912.8959276018
2319.0045248869 0.0) (11 12877.0743665158 2319.0045248869 0.0))
((0 . "LINE") (100 . "AcDbEntity") (8 . "MASONRY") (62 . 7) (370 . 13) (100 . "AcDbLine") (10 12877.0743665158
2319.0045248869 0.0) (11 12763.9521945701 2319.0045248869 0.0))
((0 . "LINE") (100 . "AcDbEntity") (8 . "MASONRY") (62 . 7) (370 . 13) (100 . "AcDbLine") (10 12779.0342307692
3423.8306108597 0.0) (11 12831.8254977376 3423.8306108597 0.0))
((0 . "LINE") (100 . "AcDbEntity") (8 . "MASONRY") (62 . 7) (370 . 13) (100 . "AcDbLine") (10 12779.0342307692
3386.1234502262 0.0) (11 12779.0342307692 3306.9379298643 0.0))
((0 . "LINE") (100 . "AcDbEntity") (8 . "MASONRY") (62 . 7) (370 . 13) (100 . "AcDbLine") (10 12784.6903393665
3186.274739819 0.0) (11 12784.6903393665 3205.1279751131 0.0))
((0 . "LINE") (100 . "AcDbEntity") (8 . "MASONRY") (62 . 7) (370 . 13) (100 . "AcDbLine") (10 12877.0702262443
3118.4014366516 0.0) (11 12877.0702262443 3131.5219230769 0.0))
((0 . "LINE") (100 . "AcDbEntity") (8 . "MASONRY") (62 . 7) (370 . 13) (100 . "AcDbLine") (10 12877.0702262443
3131.5219230769 0.0) (11 12779.0342307692 3131.5219230769 0.0))
((0 . "LINE") (100 . "AcDbEntity") (8 . "MASONRY") (62 . 7) (370 . 13) (100 . "AcDbLine") (10 12816.5570475113
3039.2159162896 0.0) (11 12816.5570475113 3048.4581900452 0.0))
((0 . "LINE") (100 . "AcDbEntity") (8 . "MASONRY") (62 . 7) (370 . 13) (100 . "AcDbLine") (10 12816.5570475113
3048.4581900452 0.0) (11 12779.0342307692 3048.4581900452 0.0))
((0 . "LINE") (100 . "AcDbEntity") (8 . "MASONRY") (62 . 7) (370 . 13) (100 . "AcDbLine") (10 13054.2986425339
2733.7860520362 0.0) (11 12779.0342307692 2733.7860520362 0.0))
((0 . "LINE") (100 . "AcDbEntity") (8 . "MASONRY") (62 . 7) (370 . 13) (100 . "AcDbLine") (10 12788.4615384615
3269.2307692308 0.0) (11 12788.4615384615 3254.3027036199 0.0))
((0 . "LINE") (100 . "AcDbEntity") (8 . "MASONRY") (62 . 7) (370 . 13) (100 . "AcDbLine") (10 12788.4615384615
3254.3027036199 0.0) (11 13001.5087556561 3254.3027036199 0.0))
((0 . "LINE") (100 . "AcDbEntity") (8 . "MASONRY") (62 . 7) (370 . 13) (100 . "AcDbLine") (10 12811.0859728507
2990.1958484163 0.0) (11 12782.8054298643 2990.1958484163 0.0))
((0 . "LINE") (100 . "AcDbEntity") (8 . "MASONRY") (62 . 7) (370 . 13) (100 . "AcDbLine") (10 12820.513280543
2895.92760181 0.0) (11 12782.8054298643 2895.92760181 0.0))
((0 . "LINE") (100 . "AcDbEntity") (8 . "MASONRY") (62 . 7) (370 . 13) (100 . "AcDbLine") (10 13034.8433371041
2635.7466063348 0.0) (11 12782.8054298643 2635.7466063348 0.0))
((0 . "LINE") (100 . "AcDbEntity") (8 . "MASONRY") (62 . 7) (370 . 13) (100 . "AcDbLine") (10 12786.5766289593
2579.185520362 0.0) (11 12861.9909502262 2579.185520362 0.0))
((0 . "LINE") (100 . "AcDbEntity") (8 . "MASONRY") (62 . 7) (370 . 13) (100 . "AcDbLine") (10 12861.9909502262
2579.185520362 0.0) (11 12990.1965384615 2579.185520362 0.0))
((0 . "LINE") (100 . "AcDbEntity") (8 . "MASONRY") (62 . 7) (370 . 13) (100 . "AcDbLine") (10 12786.5766289593
886.122760181 0.0) (11 12786.5766289593 855.9586877828 0.0))
((0 . "LINE") (100 . "AcDbEntity") (8 . "MASONRY") (62 . 7) (370 . 13) (100 . "AcDbLine") (10 12786.5766289593
886.122760181 0.0) (11 12794.1176470588 886.122760181 0.0))
((0 . "LINE") (100 . "AcDbEntity") (8 . "MASONRY") (62 . 7) (370 . 13) (100 . "AcDbLine") (10 12807.3161538462
1025.6419457014 0.0) (11 12807.3161538462 1052.036199095 0.0))
((0 . "LINE") (100 . "AcDbEntity") (8 . "MASONRY") (62 . 7) (370 . 13) (100 . "AcDbLine") (10 12839.3665158371
2990.1958484163 0.0) (11 12811.0859728507 2990.1958484163 0.0))
((0 . "LINE") (100 . "AcDbEntity") (8 . "MASONRY") (62 . 7) (370 . 13) (100 . "AcDbLine") (10 12811.0859728507
3001.5080656109 0.0) (11 12811.0859728507 2990.1958484163 0.0))
((0 . "LINE") (100 . "AcDbEntity") (8 . "MASONRY") (62 . 7) (370 . 13) (100 . "AcDbLine") (10 12807.3161538462
1052.036199095 0.0) (11 13042.9864253394 1052.036199095 0.0))
((0 . "LINE") (100 . "AcDbEntity") (8 . "MASONRY") (62 . 7) (370 . 13) (100 . "AcDbLine") (10 12820.513280543
2895.92760181 0.0) (11 12820.513280543 2926.0937443439 0.0))
((0 . "LINE") (100 . "AcDbEntity") (8 . "MASONRY") (62 . 7) (370 . 13) (100 . "AcDbLine") (10 13156.1085972851
2895.92760181 0.0) (11 12820.513280543 2895.92760181 0.0))
((0 . "LINE") (100 . "AcDbEntity") (8 . "MASONRY") (62 . 7) (370 . 13) (100 . "AcDbLine") (10 12820.513280543
2375.5656108597 0.0) (11 12854.4499321267 2375.5656108597 0.0))
((0 . "LINE") (100 . "AcDbEntity") (8 . "MASONRY") (62 . 7) (370 . 13) (100 . "AcDbLine") (10 12820.513280543
1112.3671040724 0.0) (11 12820.513280543 1097.2850678733 0.0))
((0 . "LINE") (100 . "AcDbEntity") (8 . "MASONRY") (62 . 7) (370 . 13) (100 . "AcDbLine") (10 12824.2830995475
2041.8552036199 0.0) (11 12861.9909502262 2041.8552036199 0.0))
((0 . "LINE") (100 . "AcDbEntity") (8 . "MASONRY") (62 . 7) (370 . 13) (100 . "AcDbLine") (10 12841.2528054299
3190.0452488688 0.0) (11 12841.2528054299 3182.503540724 0.0))
((0 . "LINE") (100 . "AcDbEntity") (8 . "MASONRY") (62 . 7) (370 . 13) (100 . "AcDbLine") (10 12850.6787330317
1240.5740723982 0.0) (11 12839.3665158371 1240.5740723982 0.0))
((0 . "LINE") (100 . "AcDbEntity") (8 . "MASONRY") (62 . 7) (370 . 13) (100 . "AcDbLine") (10 12899.698800905
1681.8271832579 0.0) (11 12850.6787330317 1681.8271832579 0.0))
((0 . "LINE") (100 . "AcDbEntity") (8 . "MASONRY") (62 . 7) (370 . 13) (100 . "AcDbLine") (10 12850.6787330317
1681.8271832579 0.0) (11 12850.6787330317 1730.7692307692 0.0))
((0 . "LINE") (100 . "AcDbEntity") (8 . "MASONRY") (62 . 7) (370 . 13) (100 . "AcDbLine") (10 12858.2197511312
1926.8474321267 0.0) (11 12888.3865837104 1926.8474321267 0.0))
((0 . "LINE") (100 . "AcDbEntity") (8 . "MASONRY") (62 . 7) (370 . 13) (100 . "AcDbLine") (10 12883.5824773756
509.6663348416 0.0) (11 12883.5824773756 606.1875 0.0))
((0 . "LINE") (100 . "AcDbEntity") (8 . "MASONRY") (62 . 7) (370 . 13) (100 . "AcDbLine") (10 12883.5824773756 606.1875
0.0) (11 12952.4886877828 606.1875 0.0))
((0 . "LINE") (100 . "AcDbEntity") (8 . "MASONRY") (62 . 7) (370 . 13) (100 . "AcDbLine") (10 12952.4886877828 606.1875
0.0) (11 13035.4454072398 606.1875 0.0))
((0 . "LINE") (100 . "AcDbEntity") (8 . "MASONRY") (62 . 7) (370 . 13) (100 . "AcDbLine") (10 13035.4454072398 606.1875
0.0) (11 13061.6919004525 606.1875 0.0))
((0 . "LINE") (100 . "AcDbEntity") (8 . "MASONRY") (62 . 7) (370 . 13) (100 . "AcDbLine") (10 13061.6919004525 606.1875
0.0) (11 13061.6919004525 595.7776923077 0.0))
((0 . "LINE") (100 . "AcDbEntity") (8 . "MASONRY") (62 . 7) (370 . 13) (100 . "AcDbLine") (10 13061.6919004525
595.7776923077 0.0) (11 13061.6919004525 497.7375565611 0.0))
((0 . "LINE") (100 . "AcDbEntity") (8 . "MASONRY") (62 . 7) (370 . 13) (100 . "AcDbLine") (10 12960.0297058824
3399.3985972851 0.0) (11 12873.3031674208 3399.3985972851 0.0))
((0 . "LINE") (100 . "AcDbEntity") (8 . "MASONRY") (62 . 7) (370 . 13) (100 . "AcDbLine") (10 12873.3031674208
3399.3985972851 0.0) (11 12873.3031674208 3420.06010181 0.0))
((0 . "LINE") (100 . "AcDbEntity") (8 . "MASONRY") (62 . 7) (370 . 13) (100 . "AcDbLine") (10 12865.7621493213
2982.6548303167 0.0) (11 13076.9230769231 2982.6548303167 0.0))
((0 . "LINE") (100 . "AcDbEntity") (8 . "MASONRY") (62 . 7) (370 . 13) (100 . "AcDbLine") (10 13005.2785746606
535.4454072398 0.0) (11 12910.3716628959 535.4454072398 0.0))
((0 . "LINE") (100 . "AcDbEntity") (8 . "MASONRY") (62 . 7) (370 . 13) (100 . "AcDbLine") (10 12886.5016742081
3182.503540724 0.0) (11 12877.0743665158 3182.503540724 0.0))
((0 . "LINE") (100 . "AcDbEntity") (8 . "MASONRY") (62 . 7) (370 . 13) (100 . "AcDbLine") (10 12878.9592760181
2850.6787330317 0.0) (11 12878.9592760181 2831.8248076923 0.0))
((0 . "LINE") (100 . "AcDbEntity") (8 . "MASONRY") (62 . 7) (370 . 13) (100 . "AcDbLine") (10 12888.3865837104
3082.5791855204 0.0) (11 12880.8441855204 3082.5791855204 0.0))
((0 . "LINE") (100 . "AcDbEntity") (8 . "MASONRY") (62 . 7) (370 . 13) (100 . "AcDbLine") (10 12886.5016742081
3182.503540724 0.0) (11 12886.5016742081 3156.1085972851 0.0))
((0 . "LINE") (100 . "AcDbEntity") (8 . "MASONRY") (62 . 7) (370 . 13) (100 . "AcDbLine") (10 12886.5016742081
3182.503540724 0.0) (11 12895.92760181 3182.503540724 0.0))
((0 . "LINE") (100 . "AcDbEntity") (8 . "MASONRY") (62 . 7) (370 . 13) (100 . "AcDbLine") (10 12903.4686199095
1278.2805429864 0.0) (11 12884.6153846154 1278.2805429864 0.0))
((0 . "LINE") (100 . "AcDbEntity") (8 . "MASONRY") (62 . 7) (370 . 13) (100 . "AcDbLine") (10 12888.3865837104
1953.2430656109 0.0) (11 12888.3865837104 1926.8474321267 0.0))
((0 . "LINE") (100 . "AcDbEntity") (8 . "MASONRY") (62 . 7) (370 . 13) (100 . "AcDbLine") (10 13114.6309276018
1926.8474321267 0.0) (11 12888.3865837104 1926.8474321267 0.0))
((0 . "LINE") (100 . "AcDbEntity") (8 . "MASONRY") (62 . 7) (370 . 13) (100 . "AcDbLine") (10 12892.7598529412
1572.3981900452 0.0) (11 12892.7598529412 1508.2988461538 0.0))
((0 . "LINE") (100 . "AcDbEntity") (8 . "MASONRY") (62 . 7) (370 . 13) (100 . "AcDbLine") (10 12892.7598529412
1508.2988461538 0.0) (11 12929.8642533937 1508.2988461538 0.0))
((0 . "LINE") (100 . "AcDbEntity") (8 . "MASONRY") (62 . 7) (370 . 13) (100 . "AcDbLine") (10 12967.5721040724
888.0090497738 0.0) (11 12888.3865837104 888.0090497738 0.0))
((0 . "LINE") (100 . "AcDbEntity") (8 . "MASONRY") (62 . 7) (370 . 13) (100 . "AcDbLine") (10 12892.1564027149
2039.9702941176 0.0) (11 12903.4686199095 2039.9702941176 0.0))
((0 . "LINE") (100 . "AcDbEntity") (8 . "MASONRY") (62 . 7) (370 . 13) (100 . "AcDbLine") (10 12892.1564027149
2002.2624434389 0.0) (11 12892.1564027149 1994.7207352941 0.0))
((0 . "LINE") (100 . "AcDbEntity") (8 . "MASONRY") (62 . 7) (370 . 13) (100 . "AcDbLine") (10 12895.92760181
2373.6807013575 0.0) (11 12907.2398190045 2373.6807013575 0.0))
((0 . "LINE") (100 . "AcDbEntity") (8 . "MASONRY") (62 . 7) (370 . 13) (100 . "AcDbLine") (10 12899.698800905
1681.8271832579 0.0) (11 13039.2152262443 1681.8271832579 0.0))
((0 . "LINE") (100 . "AcDbEntity") (8 . "MASONRY") (62 . 7) (370 . 13) (100 . "AcDbLine") (10 12899.698800905
1681.8271832579 0.0) (11 12899.698800905 1647.8138914027 0.0))
((0 . "LINE") (100 . "AcDbEntity") (8 . "MASONRY") (62 . 7) (370 . 13) (100 . "AcDbLine") (10 12907.2398190045
2356.7116855204 0.0) (11 12907.2398190045 2373.6807013575 0.0))
((0 . "LINE") (100 . "AcDbEntity") (8 . "MASONRY") (62 . 7) (370 . 13) (100 . "AcDbLine") (10 12907.2398190045
2373.6807013575 0.0) (11 12907.2398190045 2390.6483371041 0.0))
((0 . "LINE") (100 . "AcDbEntity") (8 . "MASONRY") (62 . 7) (370 . 13) (100 . "AcDbLine") (10 13133.4841628959
2227.2239479638 0.0) (11 12907.394479638 2227.2239479638 0.0))
((0 . "LINE") (100 . "AcDbEntity") (8 . "MASONRY") (62 . 7) (370 . 13) (100 . "AcDbLine") (10 12907.394479638
2227.2239479638 0.0) (11 12907.394479638 2250.976561086 0.0))
((0 . "LINE") (100 . "AcDbEntity") (8 . "MASONRY") (62 . 7) (370 . 13) (100 . "AcDbLine") (10 12907.394479638
2258.6729298643 0.0) (11 12907.394479638 2250.976561086 0.0))
((0 . "LINE") (100 . "AcDbEntity") (8 . "MASONRY") (62 . 7) (370 . 13) (100 . "AcDbLine") (10 12912.8959276018
2288.8383823529 0.0) (11 12912.8959276018 2319.0045248869 0.0))
((0 . "LINE") (100 . "AcDbEntity") (8 . "MASONRY") (62 . 7) (370 . 13) (100 . "AcDbLine") (10 12914.7808371041
2450.9806221719 0.0) (11 12914.7808371041 2500 0.0))
((0 . "LINE") (100 . "AcDbEntity") (8 . "MASONRY") (62 . 7) (370 . 13) (100 . "AcDbLine") (10 12914.7808371041 2500 0.0)
(11 13035.4454072398 2500 0.0))
((0 . "LINE") (100 . "AcDbEntity") (8 . "MASONRY") (62 . 7) (370 . 13) (100 . "AcDbLine") (10 13035.4454072398 2500 0.0)
(11 13035.4454072398 2526.3949434389 0.0))
((0 . "LINE") (100 . "AcDbEntity") (8 . "MASONRY") (62 . 7) (370 . 13) (100 . "AcDbLine") (10 12914.7808371041
2450.9806221719 0.0) (11 12914.7808371041 2413.2727714932 0.0))
((0 . "LINE") (100 . "AcDbEntity") (8 . "MASONRY") (62 . 7) (370 . 13) (100 . "AcDbLine") (10 13137.255361991
2319.0045248869 0.0) (11 12912.8959276018 2319.0045248869 0.0))
((0 . "LINE") (100 . "AcDbEntity") (8 . "MASONRY") (62 . 7) (370 . 13) (100 . "AcDbLine") (10 13024.1331900452
2450.9806221719 0.0) (11 12914.7808371041 2450.9806221719 0.0))
((0 . "LINE") (100 . "AcDbEntity") (8 . "MASONRY") (62 . 7) (370 . 13) (100 . "AcDbLine") (10 12929.8642533937
3188.1603393665 0.0) (11 12967.5721040724 3188.1603393665 0.0))
((0 . "LINE") (100 . "AcDbEntity") (8 . "MASONRY") (62 . 7) (370 . 13) (100 . "AcDbLine") (10 13118.4007466063
2198.3413348416 0.0) (11 12929.8642533937 2198.3413348416 0.0))
((0 . "LINE") (100 . "AcDbEntity") (8 . "MASONRY") (62 . 7) (370 . 13) (100 . "AcDbLine") (10 12967.5721040724
3150.4524886878 0.0) (11 12937.4052714932 3150.4524886878 0.0))
((0 . "LINE") (100 . "AcDbEntity") (8 . "MASONRY") (62 . 7) (370 . 13) (100 . "AcDbLine") (10 13127.8280542986
3076.874061086 0.0) (11 12937.4052714932 3076.874061086 0.0))
((0 . "LINE") (100 . "AcDbEntity") (8 . "MASONRY") (62 . 7) (370 . 13) (100 . "AcDbLine") (10 12937.4052714932
1255.5014479638 0.0) (11 12963.8078054299 1255.5014479638 0.0))
((0 . "LINE") (100 . "AcDbEntity") (8 . "MASONRY") (62 . 7) (370 . 13) (100 . "AcDbLine") (10 12963.8078054299
1255.5014479638 0.0) (11 13058.069841629 1255.5014479638 0.0))
((0 . "LINE") (100 . "AcDbEntity") (8 . "MASONRY") (62 . 7) (370 . 13) (100 . "AcDbLine") (10 13016.5907918552
1506.4097963801 0.0) (11 12941.1764705882 1506.4097963801 0.0))
((0 . "LINE") (100 . "AcDbEntity") (8 . "MASONRY") (62 . 7) (370 . 13) (100 . "AcDbLine") (10 12956.2598868778
723.0401357466 0.0) (11 13269.2307692308 723.0401357466 0.0))
((0 . "LINE") (100 . "AcDbEntity") (8 . "MASONRY") (62 . 7) (370 . 13) (100 . "AcDbLine") (10 12982.6541402715
3408.5966742081 0.0) (11 12995.2491968326 3408.5966742081 0.0))
((0 . "LINE") (100 . "AcDbEntity") (8 . "MASONRY") (62 . 7) (370 . 13) (100 . "AcDbLine") (10 12995.2491968326
3408.5966742081 0.0) (11 12995.2491968326 3389.8946493213 0.0))
((0 . "LINE") (100 . "AcDbEntity") (8 . "MASONRY") (62 . 7) (370 . 13) (100 . "AcDbLine") (10 13012.8209728507
822.0220361991 0.0) (11 12982.6541402715 822.0220361991 0.0))
((0 . "LINE") (100 . "AcDbEntity") (8 . "MASONRY") (62 . 7) (370 . 13) (100 . "AcDbLine") (10 12997.7375565611
893.665158371 0.0) (11 13012.8209728507 893.665158371 0.0))
((0 . "LINE") (100 . "AcDbEntity") (8 . "MASONRY") (62 . 7) (370 . 13) (100 . "AcDbLine") (10 13031.6742081448
3342.7601809955 0.0) (11 13001.5087556561 3342.7601809955 0.0))
((0 . "LINE") (100 . "AcDbEntity") (8 . "MASONRY") (62 . 7) (370 . 13) (100 . "AcDbLine") (10 13001.5087556561
3254.3027036199 0.0) (11 13001.5087556561 3295.6257126697 0.0))
((0 . "LINE") (100 . "AcDbEntity") (8 . "MASONRY") (62 . 7) (370 . 13) (100 . "AcDbLine") (10 13001.5087556561
3254.3027036199 0.0) (11 13009.0497737557 3254.3027036199 0.0))
((0 . "LINE") (100 . "AcDbEntity") (8 . "MASONRY") (62 . 7) (370 . 13) (100 . "AcDbLine") (10 13012.8209728507
822.0220361991 0.0) (11 13012.8209728507 893.665158371 0.0))
((0 . "LINE") (100 . "AcDbEntity") (8 . "MASONRY") (62 . 7) (370 . 13) (100 . "AcDbLine") (10 13012.8209728507
893.665158371 0.0) (11 13012.8209728507 916.2895927602 0.0))
((0 . "LINE") (100 . "AcDbEntity") (8 . "MASONRY") (62 . 7) (370 . 13) (100 . "AcDbLine") (10 13012.8209728507
935.1442081448 0.0) (11 13012.8209728507 972.850678733 0.0))
((0 . "LINE") (100 . "AcDbEntity") (8 . "MASONRY") (62 . 7) (370 . 13) (100 . "AcDbLine") (10 13034.8433371041
2635.7466063348 0.0) (11 13034.8433371041 2581.0711199095 0.0))
((0 . "LINE") (100 . "AcDbEntity") (8 . "MASONRY") (62 . 7) (370 . 13) (100 . "AcDbLine") (10 13034.8433371041
2581.0711199095 0.0) (11 13016.5907918552 2581.0711199095 0.0))
((0 . "LINE") (100 . "AcDbEntity") (8 . "MASONRY") (62 . 7) (370 . 13) (100 . "AcDbLine") (10 13012.8209728507
822.0220361991 0.0) (11 13046.7576244344 822.0220361991 0.0))
((0 . "LINE") (100 . "AcDbEntity") (8 . "MASONRY") (62 . 7) (370 . 13) (100 . "AcDbLine") (10 13024.1331900452
2450.9806221719 0.0) (11 13024.1331900452 2462.2928393665 0.0))
((0 . "LINE") (100 . "AcDbEntity") (8 . "MASONRY") (62 . 7) (370 . 13) (100 . "AcDbLine") (10 13024.1331900452
2450.9806221719 0.0) (11 13024.1331900452 2406.7812217195 0.0))
((0 . "LINE") (100 . "AcDbEntity") (8 . "MASONRY") (62 . 7) (370 . 13) (100 . "AcDbLine") (10 13024.1331900452
2406.7812217195 0.0) (11 13367.2695248869 2406.7812217195 0.0))
((0 . "LINE") (100 . "AcDbEntity") (8 . "MASONRY") (62 . 7) (370 . 13) (100 . "AcDbLine") (10 13367.2695248869
2406.7812217195 0.0) (11 13380.2098076923 2406.7812217195 0.0))
((0 . "LINE") (100 . "AcDbEntity") (8 . "MASONRY") (62 . 7) (370 . 13) (100 . "AcDbLine") (10 13380.2098076923
2406.7812217195 0.0) (11 13380.2098076923 2424.5849886878 0.0))
((0 . "LINE") (100 . "AcDbEntity") (8 . "MASONRY") (62 . 7) (370 . 13) (100 . "AcDbLine") (10 13027.9043891403
1847.6619117647 0.0) (11 13027.9043891403 1870.2863461538 0.0))
((0 . "LINE") (100 . "AcDbEntity") (8 . "MASONRY") (62 . 7) (370 . 13) (100 . "AcDbLine") (10 13026.0180995475
1817.4971493213 0.0) (11 13026.0180995475 1760.9360633484 0.0))
((0 . "LINE") (100 . "AcDbEntity") (8 . "MASONRY") (62 . 7) (370 . 13) (100 . "AcDbLine") (10 13026.0180995475
1817.4971493213 0.0) (11 13163.6496153846 1817.4971493213 0.0))
((0 . "LINE") (100 . "AcDbEntity") (8 . "MASONRY") (62 . 7) (370 . 13) (100 . "AcDbLine") (10 13024.1331900452
1442.3076923077 0.0) (11 13314.4796380091 1442.3076923077 0.0))
((0 . "LINE") (100 . "AcDbEntity") (8 . "MASONRY") (62 . 7) (370 . 13) (100 . "AcDbLine") (10 13029.787918552
1021.8693665158 0.0) (11 13029.787918552 995.4751131222 0.0))
((0 . "LINE") (100 . "AcDbEntity") (8 . "MASONRY") (62 . 7) (370 . 13) (100 . "AcDbLine") (10 13190.0452488688
995.4751131222 0.0) (11 13029.787918552 995.4751131222 0.0))
((0 . "LINE") (100 . "AcDbEntity") (8 . "MASONRY") (62 . 7) (370 . 13) (100 . "AcDbLine") (10 13034.8433371041
2635.7466063348 0.0) (11 13125.9431447964 2635.7466063348 0.0))
((0 . "LINE") (100 . "AcDbEntity") (8 . "MASONRY") (62 . 7) (370 . 13) (100 . "AcDbLine") (10 13035.4454072398
2541.4783597285 0.0) (11 13035.4454072398 2526.3949434389 0.0))
((0 . "LINE") (100 . "AcDbEntity") (8 . "MASONRY") (62 . 7) (370 . 13) (100 . "AcDbLine") (10 13054.2986425339
2526.3949434389 0.0) (11 13035.4454072398 2526.3949434389 0.0))
((0 . "LINE") (100 . "AcDbEntity") (8 . "MASONRY") (62 . 7) (370 . 13) (100 . "AcDbLine") (10 13048.6425339367
2092.7601809955 0.0) (11 13048.6425339367 2111.6141063348 0.0))
((0 . "LINE") (100 . "AcDbEntity") (8 . "MASONRY") (62 . 7) (370 . 13) (100 . "AcDbLine") (10 13048.6425339367
2111.6141063348 0.0) (11 13310.708438914 2111.6141063348 0.0))
((0 . "LINE") (100 . "AcDbEntity") (8 . "MASONRY") (62 . 7) (370 . 13) (100 . "AcDbLine") (10 13118.4007466063
2026.7724773756 0.0) (11 13042.9864253394 2026.7724773756 0.0))
((0 . "LINE") (100 . "AcDbEntity") (8 . "MASONRY") (62 . 7) (370 . 13) (100 . "AcDbLine") (10 13107.0885294118
3337.1040723982 0.0) (11 13046.7576244344 3337.1040723982 0.0))
((0 . "LINE") (100 . "AcDbEntity") (8 . "MASONRY") (62 . 7) (370 . 13) (100 . "AcDbLine") (10 13054.2986425339
2714.9321266968 0.0) (11 13054.2986425339 2733.7860520362 0.0))
((0 . "LINE") (100 . "AcDbEntity") (8 . "MASONRY") (62 . 7) (370 . 13) (100 . "AcDbLine") (10 13129.7143438914
2733.7860520362 0.0) (11 13122.1719457014 2733.7860520362 0.0))
((0 . "LINE") (100 . "AcDbEntity") (8 . "MASONRY") (62 . 7) (370 . 13) (100 . "AcDbLine") (10 13122.1719457014
2733.7860520362 0.0) (11 13054.2986425339 2733.7860520362 0.0))
((0 . "LINE") (100 . "AcDbEntity") (8 . "MASONRY") (62 . 7) (370 . 13) (100 . "AcDbLine") (10 13061.841040724
1508.2947058824 0.0) (11 13061.841040724 1519.6069230769 0.0))
((0 . "LINE") (100 . "AcDbEntity") (8 . "MASONRY") (62 . 7) (370 . 13) (100 . "AcDbLine") (10 13076.9230769231
1255.5014479638 0.0) (11 13058.069841629 1255.5014479638 0.0))
((0 . "LINE") (100 . "AcDbEntity") (8 . "MASONRY") (62 . 7) (370 . 13) (100 . "AcDbLine") (10 13076.9230769231
1255.5014479638 0.0) (11 13124.0582352941 1255.5014479638 0.0))
((0 . "LINE") (100 . "AcDbEntity") (8 . "MASONRY") (62 . 7) (370 . 13) (100 . "AcDbLine") (10 13284.3128054299
2530.2434728507 0.0) (11 13276.7717873303 2530.2434728507 0.0))
((0 . "LINE") (100 . "AcDbEntity") (8 . "MASONRY") (62 . 7) (370 . 13) (100 . "AcDbLine") (10 13276.7717873303
2530.2434728507 0.0) (11 13065.6108597285 2530.2434728507 0.0))
((0 . "LINE") (100 . "AcDbEntity") (8 . "MASONRY") (62 . 7) (370 . 13) (100 . "AcDbLine") (10 13073.1560180995
2865.761459276 0.0) (11 13073.1560180995 2827.5295588235 0.0))
((0 . "LINE") (100 . "AcDbEntity") (8 . "MASONRY") (62 . 7) (370 . 13) (100 . "AcDbLine") (10 13073.1560180995
2827.5295588235 0.0) (11 13129.7129638009 2827.5295588235 0.0))
((0 . "LINE") (100 . "AcDbEntity") (8 . "MASONRY") (62 . 7) (370 . 13) (100 . "AcDbLine") (10 13129.7129638009
2827.5295588235 0.0) (11 13129.7129638009 2800.1859502262 0.0))
((0 . "LINE") (100 . "AcDbEntity") (8 . "MASONRY") (62 . 7) (370 . 13) (100 . "AcDbLine") (10 13156.1085972851
3186.2733597285 0.0) (11 13073.1518778281 3186.2733597285 0.0))
((0 . "LINE") (100 . "AcDbEntity") (8 . "MASONRY") (62 . 7) (370 . 13) (100 . "AcDbLine") (10 13280.5429864253
1553.6209049774 0.0) (11 13078.8079864253 1553.6209049774 0.0))
((0 . "LINE") (100 . "AcDbEntity") (8 . "MASONRY") (62 . 7) (370 . 13) (100 . "AcDbLine") (10 13078.8079864253
1553.6209049774 0.0) (11 13078.8079864253 1579.9405882353 0.0))
((0 . "LINE") (100 . "AcDbEntity") (8 . "MASONRY") (62 . 7) (370 . 13) (100 . "AcDbLine") (10 13076.9230769231
3286.1839027149 0.0) (11 13156.1085972851 3286.1839027149 0.0))
((0 . "LINE") (100 . "AcDbEntity") (8 . "MASONRY") (62 . 7) (370 . 13) (100 . "AcDbLine") (10 13088.2352941176
1862.7453280543 0.0) (11 13095.7763122172 1862.7453280543 0.0))
((0 . "LINE") (100 . "AcDbEntity") (8 . "MASONRY") (62 . 7) (370 . 13) (100 . "AcDbLine") (10 13088.2352941176
1651.5837104072 0.0) (11 13088.2352941176 1644.0413122172 0.0))
((0 . "LINE") (100 . "AcDbEntity") (8 . "MASONRY") (62 . 7) (370 . 13) (100 . "AcDbLine") (10 13114.6309276018
1606.334841629 0.0) (11 13088.2352941176 1606.334841629 0.0))
((0 . "LINE") (100 . "AcDbEntity") (8 . "MASONRY") (62 . 7) (370 . 13) (100 . "AcDbLine") (10 13137.255361991
542.9864253394 0.0) (11 13088.2352941176 542.9864253394 0.0))
((0 . "LINE") (100 . "AcDbEntity") (8 . "MASONRY") (62 . 7) (370 . 13) (100 . "AcDbLine") (10 13103.3187104072
3531.2538687783 0.0) (11 13156.1085972851 3531.2538687783 0.0))
((0 . "LINE") (100 . "AcDbEntity") (8 . "MASONRY") (62 . 7) (370 . 13) (100 . "AcDbLine") (10 13107.0885294118
1862.7453280543 0.0) (11 13401.2061764706 1862.7453280543 0.0))
((0 . "LINE") (100 . "AcDbEntity") (8 . "MASONRY") (62 . 7) (370 . 13) (100 . "AcDbLine") (10 13124.0582352941
1185.8965158371 0.0) (11 13110.8597285068 1185.8965158371 0.0))
((0 . "LINE") (100 . "AcDbEntity") (8 . "MASONRY") (62 . 7) (370 . 13) (100 . "AcDbLine") (10 13401.2061764706
1961.4607126697 0.0) (11 13120.2870361991 1961.4607126697 0.0))
((0 . "LINE") (100 . "AcDbEntity") (8 . "MASONRY") (62 . 7) (370 . 13) (100 . "AcDbLine") (10 13120.2870361991
1961.4607126697 0.0) (11 13120.2870361991 1975.8675 0.0))
((0 . "LINE") (100 . "AcDbEntity") (8 . "MASONRY") (62 . 7) (370 . 13) (100 . "AcDbLine") (10 13114.6309276018
1104.8274660633 0.0) (11 13216.4408823529 1104.8274660633 0.0))
((0 . "LINE") (100 . "AcDbEntity") (8 . "MASONRY") (62 . 7) (370 . 13) (100 . "AcDbLine") (10 13114.6309276018
1104.8274660633 0.0) (11 13114.6309276018 1089.7426696833 0.0))
((0 . "LINE") (100 . "AcDbEntity") (8 . "MASONRY") (62 . 7) (370 . 13) (100 . "AcDbLine") (10 13124.0582352941
1185.8965158371 0.0) (11 13124.0582352941 1138.7641176471 0.0))
((0 . "LINE") (100 . "AcDbEntity") (8 . "MASONRY") (62 . 7) (370 . 13) (100 . "AcDbLine") (10 13122.1719457014
2979.0838574661 0.0) (11 13156.1085972851 2979.0838574661 0.0))
((0 . "LINE") (100 . "AcDbEntity") (8 . "MASONRY") (62 . 7) (370 . 13) (100 . "AcDbLine") (10 13124.0582352941
2941.1764705882 0.0) (11 13124.0582352941 2948.718178733 0.0))
((0 . "LINE") (100 . "AcDbEntity") (8 . "MASONRY") (62 . 7) (370 . 13) (100 . "AcDbLine") (10 13129.7143438914
2733.7860520362 0.0) (11 13129.7143438914 2711.1616176471 0.0))
((0 . "LINE") (100 . "AcDbEntity") (8 . "MASONRY") (62 . 7) (370 . 13) (100 . "AcDbLine") (10 13124.0582352941
1185.8965158371 0.0) (11 13129.7129638009 1185.8965158371 0.0))
((0 . "LINE") (100 . "AcDbEntity") (8 . "MASONRY") (62 . 7) (370 . 13) (100 . "AcDbLine") (10 13124.0582352941
1185.8965158371 0.0) (11 13124.0582352941 1255.5014479638 0.0))
((0 . "LINE") (100 . "AcDbEntity") (8 . "MASONRY") (62 . 7) (370 . 13) (100 . "AcDbLine") (10 13124.0582352941
1255.5014479638 0.0) (11 13124.0582352941 1255.6561085973 0.0))
((0 . "LINE") (100 . "AcDbEntity") (8 . "MASONRY") (62 . 7) (370 . 13) (100 . "AcDbLine") (10 13127.8280542986
3031.6742081448 0.0) (11 13127.8280542986 3076.874061086 0.0))
((0 . "LINE") (100 . "AcDbEntity") (8 . "MASONRY") (62 . 7) (370 . 13) (100 . "AcDbLine") (10 13127.8280542986
3076.874061086 0.0) (11 13156.1085972851 3076.874061086 0.0))
((0 . "LINE") (100 . "AcDbEntity") (8 . "MASONRY") (62 . 7) (370 . 13) (100 . "AcDbLine") (10 13125.9431447964
2665.9127488688 0.0) (11 13125.9431447964 2635.7466063348 0.0))
((0 . "LINE") (100 . "AcDbEntity") (8 . "MASONRY") (62 . 7) (370 . 13) (100 . "AcDbLine") (10 13125.9431447964
2635.7466063348 0.0) (11 13242.8351357466 2635.7466063348 0.0))
((0 . "LINE") (100 . "AcDbEntity") (8 . "MASONRY") (62 . 7) (370 . 13) (100 . "AcDbLine") (10 13269.2307692308
789.9509615385 0.0) (11 13125.9431447964 789.9509615385 0.0))
((0 . "LINE") (100 . "AcDbEntity") (8 . "MASONRY") (62 . 7) (370 . 13) (100 . "AcDbLine") (10 13125.9431447964
682.5028506787 0.0) (11 13133.4841628959 682.5028506787 0.0))
((0 . "LINE") (100 . "AcDbEntity") (8 . "MASONRY") (62 . 7) (370 . 13) (100 . "AcDbLine") (10 13129.7129638009
2779.0349208145 0.0) (11 13129.7129638009 2800.1859502262 0.0))
((0 . "LINE") (100 . "AcDbEntity") (8 . "MASONRY") (62 . 7) (370 . 13) (100 . "AcDbLine") (10 13159.8797963801
1753.3936651584 0.0) (11 13133.4841628959 1753.3936651584 0.0))
((0 . "LINE") (100 . "AcDbEntity") (8 . "MASONRY") (62 . 7) (370 . 13) (100 . "AcDbLine") (10 13134.0862330317
1308.4473755656 0.0) (11 13134.0862330317 1338.6114479638 0.0))
((0 . "LINE") (100 . "AcDbEntity") (8 . "MASONRY") (62 . 7) (370 . 13) (100 . "AcDbLine") (10 13134.0862330317
1338.6114479638 0.0) (11 13152.33739819 1338.6114479638 0.0))
((0 . "LINE") (100 . "AcDbEntity") (8 . "MASONRY") (62 . 7) (370 . 13) (100 . "AcDbLine") (10 13152.33739819
1338.6114479638 0.0) (11 13227.7530995475 1338.6114479638 0.0))
((0 . "LINE") (100 . "AcDbEntity") (8 . "MASONRY") (62 . 7) (370 . 13) (100 . "AcDbLine") (10 13129.7143438914
2733.7860520362 0.0) (11 13156.1085972851 2733.7860520362 0.0))
((0 . "LINE") (100 . "AcDbEntity") (8 . "MASONRY") (62 . 7) (370 . 13) (100 . "AcDbLine") (10 13137.255361991
2319.0045248869 0.0) (11 13137.255361991 2285.0678733032 0.0))
((0 . "LINE") (100 . "AcDbEntity") (8 . "MASONRY") (62 . 7) (370 . 13) (100 . "AcDbLine") (10 13137.255361991
2319.0045248869 0.0) (11 13650.0749547511 2319.0045248869 0.0))
((0 . "LINE") (100 . "AcDbEntity") (8 . "MASONRY") (62 . 7) (370 . 13) (100 . "AcDbLine") (10 13137.255361991
2156.8629751131 0.0) (11 13137.255361991 2168.1751923077 0.0))
((0 . "LINE") (100 . "AcDbEntity") (8 . "MASONRY") (62 . 7) (370 . 13) (100 . "AcDbLine") (10 13137.255361991
1602.5650226244 0.0) (11 13332.0500339367 1602.5650226244 0.0))
((0 . "LINE") (100 . "AcDbEntity") (8 . "MASONRY") (62 . 7) (370 . 13) (100 . "AcDbLine") (10 13332.0500339367
1602.5650226244 0.0) (11 13340.8752714932 1602.5650226244 0.0))
((0 . "LINE") (100 . "AcDbEntity") (8 . "MASONRY") (62 . 7) (370 . 13) (100 . "AcDbLine") (10 13124.0582352941
1255.6561085973 0.0) (11 13237.1804072398 1255.6561085973 0.0))
((0 . "LINE") (100 . "AcDbEntity") (8 . "MASONRY") (62 . 7) (370 . 13) (100 . "AcDbLine") (10 13141.0251809955
3338.9889819005 0.0) (11 13152.33739819 3338.9889819005 0.0))
((0 . "LINE") (100 . "AcDbEntity") (8 . "MASONRY") (62 . 7) (370 . 13) (100 . "AcDbLine") (10 13129.7129638009
2800.1859502262 0.0) (11 13156.1085972851 2800.1859502262 0.0))
((0 . "LINE") (100 . "AcDbEntity") (8 . "MASONRY") (62 . 7) (370 . 13) (100 . "AcDbLine") (10 13141.0251809955
2194.5701357466 0.0) (11 13159.8797963801 2194.5701357466 0.0))
((0 . "LINE") (100 . "AcDbEntity") (8 . "MASONRY") (62 . 7) (370 . 13) (100 . "AcDbLine") (10 13141.0251809955
1668.5520361991 0.0) (11 13401.2061764706 1668.5520361991 0.0))
((0 . "LINE") (100 . "AcDbEntity") (8 . "MASONRY") (62 . 7) (370 . 13) (100 . "AcDbLine") (10 13171.1920135747
629.7143438914 0.0) (11 13269.2307692308 629.7143438914 0.0))
((0 . "LINE") (100 . "AcDbEntity") (8 . "MASONRY") (62 . 7) (370 . 13) (100 . "AcDbLine") (10 13190.0452488688
2462.2928393665 0.0) (11 13178.7330316742 2462.2928393665 0.0))
((0 . "LINE") (100 . "AcDbEntity") (8 . "MASONRY") (62 . 7) (370 . 13) (100 . "AcDbLine") (10 13190.0452488688
2198.3406447964 0.0) (11 13388.0090497738 2198.3406447964 0.0))
((0 . "LINE") (100 . "AcDbEntity") (8 . "MASONRY") (62 . 7) (370 . 13) (100 . "AcDbLine") (10 13205.1286651584
1819.3820588235 0.0) (11 13193.8164479638 1819.3820588235 0.0))
((0 . "LINE") (100 . "AcDbEntity") (8 . "MASONRY") (62 . 7) (370 . 13) (100 . "AcDbLine") (10 13203.2437556561
942.6838461538 0.0) (11 13203.2437556561 837.1040723982 0.0))
((0 . "LINE") (100 . "AcDbEntity") (8 . "MASONRY") (62 . 7) (370 . 13) (100 . "AcDbLine") (10 13223.9819004525
1753.3936651584 0.0) (11 13205.1286651584 1753.3936651584 0.0))
((0 . "LINE") (100 . "AcDbEntity") (8 . "MASONRY") (62 . 7) (370 . 13) (100 . "AcDbLine") (10 13226.6028167421
530.878178733 0.0) (11 13226.6028167421 535.4440271493 0.0))
((0 . "LINE") (100 . "AcDbEntity") (8 . "MASONRY") (62 . 7) (370 . 13) (100 . "AcDbLine") (10 13237.1804072398
1244.3438914027 0.0) (11 13237.1804072398 1255.6561085973 0.0))
((0 . "LINE") (100 . "AcDbEntity") (8 . "MASONRY") (62 . 7) (370 . 13) (100 . "AcDbLine") (10 13397.4363574661
1255.6561085973 0.0) (11 13237.1804072398 1255.6561085973 0.0))
((0 . "LINE") (100 . "AcDbEntity") (8 . "MASONRY") (62 . 7) (370 . 13) (100 . "AcDbLine") (10 13276.7717873303
1344.2689366516 0.0) (11 13246.6063348416 1344.2689366516 0.0))
((0 . "LINE") (100 . "AcDbEntity") (8 . "MASONRY") (62 . 7) (370 . 13) (100 . "AcDbLine") (10 13279.0525339367
992.9681108597 0.0) (11 13246.6063348416 992.9681108597 0.0))
((0 . "LINE") (100 . "AcDbEntity") (8 . "MASONRY") (62 . 7) (370 . 13) (100 . "AcDbLine") (10 13397.4363574661
1743.9663574661 0.0) (11 13250.3775339367 1743.9663574661 0.0))
((0 . "LINE") (100 . "AcDbEntity") (8 . "MASONRY") (62 . 7) (370 . 13) (100 . "AcDbLine") (10 13273.6040384615
1380.0904977376 0.0) (11 13273.6040384615 1417.79489819 0.0))
((0 . "LINE") (100 . "AcDbEntity") (8 . "MASONRY") (62 . 7) (370 . 13) (100 . "AcDbLine") (10 13273.6040384615
1417.79489819 0.0) (11 13288.0840045249 1417.79489819 0.0))
((0 . "LINE") (100 . "AcDbEntity") (8 . "MASONRY") (62 . 7) (370 . 13) (100 . "AcDbLine") (10 13284.3128054299
2530.2434728507 0.0) (11 13284.3128054299 2586.7272285068 0.0))
((0 . "LINE") (100 . "AcDbEntity") (8 . "MASONRY") (62 . 7) (370 . 13) (100 . "AcDbLine") (10 13288.0840045249
2624.4343891403 0.0) (11 13288.0840045249 2613.1221719457 0.0))
((0 . "LINE") (100 . "AcDbEntity") (8 . "MASONRY") (62 . 7) (370 . 13) (100 . "AcDbLine") (10 13286.2764253394
1089.7426696833 0.0) (11 13286.2764253394 1101.8668438914 0.0))
((0 . "LINE") (100 . "AcDbEntity") (8 . "MASONRY") (62 . 7) (370 . 13) (100 . "AcDbLine") (10 13286.2764253394
1101.8668438914 0.0) (11 13313.0833936652 1101.8668438914 0.0))
((0 . "LINE") (100 . "AcDbEntity") (8 . "MASONRY") (62 . 7) (370 . 13) (100 . "AcDbLine") (10 13288.0840045249
2624.4343891403 0.0) (11 13288.0840045249 2658.371040724 0.0))
((0 . "LINE") (100 . "AcDbEntity") (8 . "MASONRY") (62 . 7) (370 . 13) (100 . "AcDbLine") (10 13288.0840045249
2624.4343891403 0.0) (11 13699.0950226244 2624.4343891403 0.0))
((0 . "LINE") (100 . "AcDbEntity") (8 . "MASONRY") (62 . 7) (370 . 13) (100 . "AcDbLine") (10 13284.3128054299
2530.2434728507 0.0) (11 13340.8752714932 2530.2434728507 0.0))
((0 . "LINE") (100 . "AcDbEntity") (8 . "MASONRY") (62 . 7) (370 . 13) (100 . "AcDbLine") (10 13314.4796380091
1429.1091855204 0.0) (11 13314.4796380091 1438.5364932127 0.0))
((0 . "LINE") (100 . "AcDbEntity") (8 . "MASONRY") (62 . 7) (370 . 13) (100 . "AcDbLine") (10 13310.708438914
2032.4285859729 0.0) (11 13310.708438914 2043.7470135747 0.0))
((0 . "LINE") (100 . "AcDbEntity") (8 . "MASONRY") (62 . 7) (370 . 13) (100 . "AcDbLine") (10 13310.708438914
2043.7470135747 0.0) (11 13310.708438914 2111.6141063348 0.0))
((0 . "LINE") (100 . "AcDbEntity") (8 . "MASONRY") (62 . 7) (370 . 13) (100 . "AcDbLine") (10 13397.4363574661
2111.6141063348 0.0) (11 13310.708438914 2111.6141063348 0.0))
((0 . "LINE") (100 . "AcDbEntity") (8 . "MASONRY") (62 . 7) (370 . 13) (100 . "AcDbLine") (10 13314.4796380091
1442.3076923077 0.0) (11 13314.4796380091 1474.3580542986 0.0))
((0 . "LINE") (100 . "AcDbEntity") (8 . "MASONRY") (62 . 7) (370 . 13) (100 . "AcDbLine") (10 13314.4796380091
1438.5364932127 0.0) (11 13397.4363574661 1438.5364932127 0.0))
((0 . "LINE") (100 . "AcDbEntity") (8 . "MASONRY") (62 . 7) (370 . 13) (100 . "AcDbLine") (10 13329.5630542986
1338.6114479638 0.0) (11 13397.4363574661 1338.6114479638 0.0))
((0 . "LINE") (100 . "AcDbEntity") (8 . "MASONRY") (62 . 7) (370 . 13) (100 . "AcDbLine") (10 13329.5630542986
1219.8345475113 0.0) (11 13352.1874886878 1219.8345475113 0.0))
((0 . "LINE") (100 . "AcDbEntity") (8 . "MASONRY") (62 . 7) (370 . 13) (100 . "AcDbLine") (10 13340.8752714932
1636.5016742081 0.0) (11 13340.8752714932 1602.5650226244 0.0))
((0 . "LINE") (100 . "AcDbEntity") (8 . "MASONRY") (62 . 7) (370 . 13) (100 . "AcDbLine") (10 13332.0500339367
1602.5650226244 0.0) (11 13332.0500339367 1538.465678733 0.0))
((0 . "LINE") (100 . "AcDbEntity") (8 . "MASONRY") (62 . 7) (370 . 13) (100 . "AcDbLine") (10 13332.0500339367
1538.465678733 0.0) (11 13393.665158371 1538.465678733 0.0))
((0 . "LINE") (100 . "AcDbEntity") (8 . "MASONRY") (62 . 7) (370 . 13) (100 . "AcDbLine") (10 13340.8752714932
1602.5650226244 0.0) (11 13397.4363574661 1602.5650226244 0.0))
((0 . "LINE") (100 . "AcDbEntity") (8 . "MASONRY") (62 . 7) (370 . 13) (100 . "AcDbLine") (10 13388.0090497738
2526.3949434389 0.0) (11 13363.4997058824 2526.3949434389 0.0))
((0 . "LINE") (100 . "AcDbEntity") (8 . "MASONRY") (62 . 7) (370 . 13) (100 . "AcDbLine") (10 13552.036199095
561.841040724 0.0) (11 13388.8886764706 561.841040724 0.0))
((0 . "LINE") (100 . "AcDbEntity") (8 . "MASONRY") (62 . 7) (370 . 13) (100 . "AcDbLine") (10 13470.2421832579
505.7853619909 0.0) (11 13506.7873303167 505.7853619909 0.0))
((0 . "LINE") (100 . "AcDbEntity") (8 . "MASONRY") (62 . 7) (370 . 13) (100 . "AcDbLine") (10 13388.0090497738
2526.3949434389 0.0) (11 13388.0090497738 2466.0633484163 0.0))
((0 . "LINE") (100 . "AcDbEntity") (8 . "MASONRY") (62 . 7) (370 . 13) (100 . "AcDbLine") (10 13388.0090497738
2292.609581448 0.0) (11 13388.0090497738 2198.3406447964 0.0))
((0 . "LINE") (100 . "AcDbEntity") (8 . "MASONRY") (62 . 7) (370 . 13) (100 . "AcDbLine") (10 13388.0090497738
2526.3949434389 0.0) (11 13691.5540045249 2526.3949434389 0.0))
((0 . "LINE") (100 . "AcDbEntity") (8 . "MASONRY") (62 . 7) (370 . 13) (100 . "AcDbLine") (10 13404.9773755656
2198.3406447964 0.0) (11 13388.0090497738 2198.3406447964 0.0))
((0 . "LINE") (100 . "AcDbEntity") (8 . "MASONRY") (62 . 7) (370 . 13) (100 . "AcDbLine") (10 13457.7672624434
2405.7317533937 0.0) (11 13450.2262443439 2405.7317533937 0.0))
((0 . "LINE") (100 . "AcDbEntity") (8 . "MASONRY") (62 . 7) (370 . 13) (100 . "AcDbLine") (10 13457.8487330317
1218.987918552 0.0) (11 13457.8487330317 2314.1810859729 0.0))
((0 . "LINE") (100 . "AcDbEntity") (8 . "MASONRY") (62 . 7) (370 . 13) (100 . "AcDbLine") (10 13457.8487330317
2314.1810859729 0.0) (11 13476.6218778281 2314.1810859729 0.0))
((0 . "LINE") (100 . "AcDbEntity") (8 . "MASONRY") (62 . 7) (370 . 13) (100 . "AcDbLine") (10 13476.6218778281
2314.1810859729 0.0) (11 13569.9462895928 2314.1810859729 0.0))
((0 . "LINE") (100 . "AcDbEntity") (8 . "MASONRY") (62 . 7) (370 . 13) (100 . "AcDbLine") (10 13516.7393778281
2488.6877828054 0.0) (11 13516.7393778281 2450.9806221719 0.0))
((0 . "LINE") (100 . "AcDbEntity") (8 . "MASONRY") (62 . 7) (370 . 13) (100 . "AcDbLine") (10 13516.7393778281
2450.9806221719 0.0) (11 13516.7393778281 2413.2727714932 0.0))
((0 . "LINE") (100 . "AcDbEntity") (8 . "MASONRY") (62 . 7) (370 . 13) (100 . "AcDbLine") (10 13516.7393778281
2413.2727714932 0.0) (11 13516.7393778281 2401.9605542986 0.0))
((0 . "LINE") (100 . "AcDbEntity") (8 . "MASONRY") (62 . 7) (370 . 13) (100 . "AcDbLine") (10 13514.3283484163
2360.4828846154 0.0) (11 13521.8707466063 2360.4828846154 0.0))
((0 . "LINE") (100 . "AcDbEntity") (8 . "MASONRY") (62 . 7) (370 . 13) (100 . "AcDbLine") (10 13552.036199095
561.841040724 0.0) (11 13702.8662217195 561.841040724 0.0))
((0 . "LINE") (100 . "AcDbEntity") (8 . "MASONRY") (62 . 7) (370 . 13) (100 . "AcDbLine") (10 13719.4575678733
561.841040724 0.0) (11 14233.409479638 561.841040724 0.0))
((0 . "LINE") (100 . "AcDbEntity") (8 . "MASONRY") (62 . 7) (370 . 13) (100 . "AcDbLine") (10 14252.0224434389
563.5436764706 0.0) (11 15314.8376131222 563.5436764706 0.0))
((0 . "LINE") (100 . "AcDbEntity") (8 . "MASONRY") (62 . 7) (370 . 13) (100 . "AcDbLine") (10 15367.4785859729
565.5169570136 0.0) (11 15433.6368325792 565.5169570136 0.0))
((0 . "LINE") (100 . "AcDbEntity") (8 . "MASONRY") (62 . 7) (370 . 13) (100 . "AcDbLine") (10 13552.036199095
561.841040724 0.0) (11 13552.036199095 512.8195927602 0.0))
((0 . "LINE") (100 . "AcDbEntity") (8 . "MASONRY") (62 . 7) (370 . 13) (100 . "AcDbLine") (10 13569.9462895928
2205.8823529412 0.0) (11 13569.9462895928 2314.1810859729 0.0))
((0 . "LINE") (100 . "AcDbEntity") (8 . "MASONRY") (62 . 7) (370 . 13) (100 . "AcDbLine") (10 15659.8784162896
2205.8823529412 0.0) (11 15659.8784162896 2314.1810859729 0.0))
((0 . "LINE") (100 . "AcDbEntity") (8 . "MASONRY") (62 . 7) (370 . 13) (100 . "AcDbLine") (10 15659.8784162896
2314.1810859729 0.0) (11 15565.6108597285 2314.1810859729 0.0))
((0 . "LINE") (100 . "AcDbEntity") (8 . "MASONRY") (62 . 7) (370 . 13) (100 . "AcDbLine") (10 15565.6108597285
2314.1810859729 0.0) (11 15384.6153846154 2314.1810859729 0.0))
((0 . "LINE") (100 . "AcDbEntity") (8 . "MASONRY") (62 . 7) (370 . 13) (100 . "AcDbLine") (10 15384.6153846154
2314.1810859729 0.0) (11 15177.8309502262 2314.1810859729 0.0))
((0 . "LINE") (100 . "AcDbEntity") (8 . "MASONRY") (62 . 7) (370 . 13) (100 . "AcDbLine") (10 13996.3771945701
2314.1810859729 0.0) (11 13827.3006108597 2314.1810859729 0.0))
((0 . "LINE") (100 . "AcDbEntity") (8 . "MASONRY") (62 . 7) (370 . 13) (100 . "AcDbLine") (10 13827.3006108597
2314.1810859729 0.0) (11 13569.9462895928 2314.1810859729 0.0))
((0 . "LINE") (100 . "AcDbEntity") (8 . "MASONRY") (62 . 7) (370 . 13) (100 . "AcDbLine") (10 13706.636040724
2624.4343891403 0.0) (11 13699.0950226244 2624.4343891403 0.0))
((0 . "LINE") (100 . "AcDbEntity") (8 . "MASONRY") (62 . 7) (370 . 13) (100 . "AcDbLine") (10 13699.0950226244
2586.7272285068 0.0) (11 13699.0950226244 2624.4343891403 0.0))
((0 . "LINE") (100 . "AcDbEntity") (8 . "MASONRY") (62 . 7) (370 . 13) (100 . "AcDbLine") (10 13702.8662217195
2662.1415497738 0.0) (11 13691.5540045249 2662.1415497738 0.0))
((0 . "LINE") (100 . "AcDbEntity") (8 . "MASONRY") (62 . 7) (370 . 13) (100 . "AcDbLine") (10 13691.5540045249
2549.0193778281 0.0) (11 13691.5540045249 2526.3949434389 0.0))
((0 . "LINE") (100 . "AcDbEntity") (8 . "MASONRY") (62 . 7) (370 . 13) (100 . "AcDbLine") (10 13921.5681674208
2526.3949434389 0.0) (11 13691.5540045249 2526.3949434389 0.0))
((0 . "LINE") (100 . "AcDbEntity") (8 . "MASONRY") (62 . 7) (370 . 13) (100 . "AcDbLine") (10 13693.4389140272
2432.1266968326 0.0) (11 13693.4389140272 2473.6050565611 0.0))
((0 . "LINE") (100 . "AcDbEntity") (8 . "MASONRY") (62 . 7) (370 . 13) (100 . "AcDbLine") (10 13699.0950226244
2586.7272285068 0.0) (11 13699.0950226244 2575.4150113122 0.0))
((0 . "LINE") (100 . "AcDbEntity") (8 . "MASONRY") (62 . 7) (370 . 13) (100 . "AcDbLine") (10 13699.0950226244
2386.8778280543 0.0) (11 13815.9883936652 2386.8778280543 0.0))
((0 . "LINE") (100 . "AcDbEntity") (8 . "MASONRY") (62 . 7) (370 . 13) (100 . "AcDbLine") (10 13699.0950226244
2586.7272285068 0.0) (11 13721.7194570136 2586.7272285068 0.0))
((0 . "LINE") (100 . "AcDbEntity") (8 . "MASONRY") (62 . 7) (370 . 13) (100 . "AcDbLine") (10 13932.8803846154
2624.4343891403 0.0) (11 13914.0271493213 2624.4343891403 0.0))
((0 . "LINE") (100 . "AcDbEntity") (8 . "MASONRY") (62 . 7) (370 . 13) (100 . "AcDbLine") (10 13914.0271493213
2624.4343891403 0.0) (11 13725.4906561086 2624.4343891403 0.0))
((0 . "LINE") (100 . "AcDbEntity") (8 . "MASONRY") (62 . 7) (370 . 13) (100 . "AcDbLine") (10 13921.5681674208
2526.3949434389 0.0) (11 13921.5681674208 2571.6438122172 0.0))
((0 . "LINE") (100 . "AcDbEntity") (8 . "MASONRY") (62 . 7) (370 . 13) (100 . "AcDbLine") (10 13921.5681674208
2571.6438122172 0.0) (11 13921.5681674208 2588.0107579186 0.0))
((0 . "LINE") (100 . "AcDbEntity") (8 . "MASONRY") (62 . 7) (370 . 13) (100 . "AcDbLine") (10 13921.5681674208
2588.0107579186 0.0) (11 13744.3438914027 2588.0107579186 0.0))
((0 . "LINE") (100 . "AcDbEntity") (8 . "MASONRY") (62 . 7) (370 . 13) (100 . "AcDbLine") (10 13862.5811538462
2231.1553280543 0.0) (11 13778.0526923077 2231.1553280543 0.0))
((0 . "LINE") (100 . "AcDbEntity") (8 . "MASONRY") (62 . 7) (370 . 13) (100 . "AcDbLine") (10 13876.3192986425
514.8287782805 0.0) (11 13836.515260181 514.8287782805 0.0))
((0 . "LINE") (100 . "AcDbEntity") (8 . "MASONRY") (62 . 7) (370 . 13) (100 . "AcDbLine") (10 13842.3826470588
2269.9851470588 0.0) (11 13834.8416289593 2269.9851470588 0.0))
((0 . "LINE") (100 . "AcDbEntity") (8 . "MASONRY") (62 . 7) (370 . 13) (100 . "AcDbLine") (10 13876.3192986425
2281.2973642534 0.0) (11 13865.007081448 2281.2973642534 0.0))
((0 . "LINE") (100 . "AcDbEntity") (8 . "MASONRY") (62 . 7) (370 . 13) (100 . "AcDbLine") (10 13891.4027149321
2315.9582918552 0.0) (11 13999.7076470588 2315.9582918552 0.0))
((0 . "LINE") (100 . "AcDbEntity") (8 . "MASONRY") (62 . 7) (370 . 13) (100 . "AcDbLine") (10 15185.388438914
2310.1033371041 0.0) (11 15263.9535746606 2310.1033371041 0.0))
((0 . "LINE") (100 . "AcDbEntity") (8 . "MASONRY") (62 . 7) (370 . 13) (100 . "AcDbLine") (10 13921.5681674208
2526.3949434389 0.0) (11 13978.1292533937 2526.3949434389 0.0))
((0 . "LINE") (100 . "AcDbEntity") (8 . "MASONRY") (62 . 7) (370 . 13) (100 . "AcDbLine") (10 13978.1292533937
2526.3949434389 0.0) (11 14151.5837104072 2526.3949434389 0.0))
((0 . "LINE") (100 . "AcDbEntity") (8 . "MASONRY") (62 . 7) (370 . 13) (100 . "AcDbLine") (10 14136.5002941176
2665.9127488688 0.0) (11 13929.1105656109 2665.9127488688 0.0))
((0 . "LINE") (100 . "AcDbEntity") (8 . "MASONRY") (62 . 7) (370 . 13) (100 . "AcDbLine") (10 13937.2978393665
471.0731108597 0.0) (11 13937.2978393665 490.195158371 0.0))
((0 . "LINE") (100 . "AcDbEntity") (8 . "MASONRY") (62 . 7) (370 . 13) (100 . "AcDbLine") (10 13970.5882352941
2466.0633484163 0.0) (11 13970.5882352941 2432.1266968326 0.0))
((0 . "LINE") (100 . "AcDbEntity") (8 . "MASONRY") (62 . 7) (370 . 13) (100 . "AcDbLine") (10 13970.5882352941
2575.4150113122 0.0) (11 14095.0226244344 2575.4150113122 0.0))
((0 . "LINE") (100 . "AcDbEntity") (8 . "MASONRY") (62 . 7) (370 . 13) (100 . "AcDbLine") (10 13985.6716515837
2631.9760972851 0.0) (11 14125.1880769231 2631.9760972851 0.0))
((0 . "LINE") (100 . "AcDbEntity") (8 . "MASONRY") (62 . 7) (370 . 13) (100 . "AcDbLine") (10 14008.2960859729
516.5921719457 0.0) (11 13985.6716515837 516.5921719457 0.0))
((0 . "LINE") (100 . "AcDbEntity") (8 . "MASONRY") (62 . 7) (370 . 13) (100 . "AcDbLine") (10 14132.7304751131
2575.4150113122 0.0) (11 14151.5837104072 2575.4150113122 0.0))
((0 . "LINE") (100 . "AcDbEntity") (8 . "MASONRY") (62 . 7) (370 . 13) (100 . "AcDbLine") (10 14151.5837104072
2575.4150113122 0.0) (11 14151.5837104072 2526.3949434389 0.0))
((0 . "LINE") (100 . "AcDbEntity") (8 . "MASONRY") (62 . 7) (370 . 13) (100 . "AcDbLine") (10 14151.5837104072
2586.7265384615 0.0) (11 14151.5837104072 2575.4150113122 0.0))
((0 . "LINE") (100 . "AcDbEntity") (8 . "MASONRY") (62 . 7) (370 . 13) (100 . "AcDbLine") (10 14151.5837104072
2586.7265384615 0.0) (11 14151.5837104072 2598.0394457014 0.0))
((0 . "LINE") (100 . "AcDbEntity") (8 . "MASONRY") (62 . 7) (370 . 13) (100 . "AcDbLine") (10 14151.5837104072
2586.7265384615 0.0) (11 14174.2081447964 2586.7265384615 0.0))
((0 . "LINE") (100 . "AcDbEntity") (8 . "MASONRY") (62 . 7) (370 . 13) (100 . "AcDbLine") (10 14176.0930542986
2662.1415497738 0.0) (11 14155.3549095023 2662.1415497738 0.0))
((0 . "LINE") (100 . "AcDbEntity") (8 . "MASONRY") (62 . 7) (370 . 13) (100 . "AcDbLine") (10 14166.6671266968
2526.3949434389 0.0) (11 14151.5837104072 2526.3949434389 0.0))
((0 . "LINE") (100 . "AcDbEntity") (8 . "MASONRY") (62 . 7) (370 . 13) (100 . "AcDbLine") (10 14166.6671266968
2526.3949434389 0.0) (11 14166.6671266968 2511.3122171946 0.0))
((0 . "LINE") (100 . "AcDbEntity") (8 . "MASONRY") (62 . 7) (370 . 13) (100 . "AcDbLine") (10 14347.66260181
2526.3949434389 0.0) (11 14166.6671266968 2526.3949434389 0.0))
((0 . "LINE") (100 . "AcDbEntity") (8 . "MASONRY") (62 . 7) (370 . 13) (100 . "AcDbLine") (10 14166.6671266968
2484.9172737557 0.0) (11 14166.6671266968 2477.3755656109 0.0))
((0 . "LINE") (100 . "AcDbEntity") (8 . "MASONRY") (62 . 7) (370 . 13) (100 . "AcDbLine") (10 14176.0930542986
2662.1415497738 0.0) (11 14176.0930542986 2635.7466063348 0.0))
((0 . "LINE") (100 . "AcDbEntity") (8 . "MASONRY") (62 . 7) (370 . 13) (100 . "AcDbLine") (10 14176.0930542986
2662.1415497738 0.0) (11 14357.0885294118 2662.1415497738 0.0))
((0 . "LINE") (100 . "AcDbEntity") (8 . "MASONRY") (62 . 7) (370 . 13) (100 . "AcDbLine") (10 14351.4324208145
2582.956719457 0.0) (11 14196.8325791855 2582.956719457 0.0))
((0 . "LINE") (100 . "AcDbEntity") (8 . "MASONRY") (62 . 7) (370 . 13) (100 . "AcDbLine") (10 14309.9547511312
2631.9760972851 0.0) (11 14223.2282126697 2631.9760972851 0.0))
((0 . "LINE") (100 . "AcDbEntity") (8 . "MASONRY") (62 . 7) (370 . 13) (100 . "AcDbLine") (10 14438.1603393665
516.5907918552 0.0) (11 14371.3213235294 516.5907918552 0.0))
((0 . "LINE") (100 . "AcDbEntity") (8 . "MASONRY") (62 . 7) (370 . 13) (100 . "AcDbLine") (10 14347.66260181
2526.3949434389 0.0) (11 14347.66260181 2549.0193778281 0.0))
((0 . "LINE") (100 . "AcDbEntity") (8 . "MASONRY") (62 . 7) (370 . 13) (100 . "AcDbLine") (10 14611.6134162896
2526.3949434389 0.0) (11 14347.66260181 2526.3949434389 0.0))
((0 . "LINE") (100 . "AcDbEntity") (8 . "MASONRY") (62 . 7) (370 . 13) (100 . "AcDbLine") (10 14913.2734615385
2662.1415497738 0.0) (11 14357.0885294118 2662.1415497738 0.0))
((0 . "LINE") (100 . "AcDbEntity") (8 . "MASONRY") (62 . 7) (370 . 13) (100 . "AcDbLine") (10 14913.2734615385
2631.9760972851 0.0) (11 14357.0885294118 2631.9760972851 0.0))
((0 . "LINE") (100 . "AcDbEntity") (8 . "MASONRY") (62 . 7) (370 . 13) (100 . "AcDbLine") (10 14357.0885294118
2631.9760972851 0.0) (11 14357.0885294118 2662.1415497738 0.0))
((0 . "LINE") (100 . "AcDbEntity") (8 . "MASONRY") (62 . 7) (370 . 13) (100 . "AcDbLine") (10 14490.9502262443
476.9980316742 0.0) (11 14498.4912443439 476.9980316742 0.0))
((0 . "LINE") (100 . "AcDbEntity") (8 . "MASONRY") (62 . 7) (370 . 13) (100 . "AcDbLine") (10 14498.4912443439
501.5073755656 0.0) (11 14498.4912443439 476.9980316742 0.0))
((0 . "LINE") (100 . "AcDbEntity") (8 . "MASONRY") (62 . 7) (370 . 13) (100 . "AcDbLine") (10 14498.4912443439
468.3519683258 0.0) (11 14498.4912443439 476.9980316742 0.0))
((0 . "LINE") (100 . "AcDbEntity") (8 . "MASONRY") (62 . 7) (370 . 13) (100 . "AcDbLine") (10 14630.4680316742
501.5073755656 0.0) (11 14562.5947285068 501.5073755656 0.0))
((0 . "LINE") (100 . "AcDbEntity") (8 . "MASONRY") (62 . 7) (370 . 13) (100 . "AcDbLine") (10 14641.7802488688
2524.5093438914 0.0) (11 14868.0245927602 2524.5093438914 0.0))
((0 . "LINE") (100 . "AcDbEntity") (8 . "MASONRY") (62 . 7) (370 . 13) (100 . "AcDbLine") (10 15124.4343891403
2526.3949434389 0.0) (11 14890.6490271493 2526.3949434389 0.0))
((0 . "LINE") (100 . "AcDbEntity") (8 . "MASONRY") (62 . 7) (370 . 13) (100 . "AcDbLine") (10 15256.4084162896
2662.1415497738 0.0) (11 14913.2734615385 2662.1415497738 0.0))
((0 . "LINE") (100 . "AcDbEntity") (8 . "MASONRY") (62 . 7) (370 . 13) (100 . "AcDbLine") (10 14913.2734615385
2662.1415497738 0.0) (11 14913.2734615385 2631.9760972851 0.0))
((0 . "LINE") (100 . "AcDbEntity") (8 . "MASONRY") (62 . 7) (370 . 13) (100 . "AcDbLine") (10 15256.4084162896
2631.9760972851 0.0) (11 14913.2734615385 2631.9760972851 0.0))
((0 . "LINE") (100 . "AcDbEntity") (8 . "MASONRY") (62 . 7) (370 . 13) (100 . "AcDbLine") (10 15308.4622850679
2239.8190045249 0.0) (11 15299.3028846154 2239.8190045249 0.0))
((0 . "LINE") (100 . "AcDbEntity") (8 . "MASONRY") (62 . 7) (370 . 13) (100 . "AcDbLine") (10 15026.3956334842
516.5907918552 0.0) (11 15041.9126470588 516.5907918552 0.0))
((0 . "LINE") (100 . "AcDbEntity") (8 . "MASONRY") (62 . 7) (370 . 13) (100 . "AcDbLine") (10 15041.9126470588
516.5907918552 0.0) (11 15041.9126470588 459.1709502262 0.0))
((0 . "LINE") (100 . "AcDbEntity") (8 . "MASONRY") (62 . 7) (370 . 13) (100 . "AcDbLine") (10 15120.6631900452
2575.4150113122 0.0) (11 15128.2055882353 2575.4150113122 0.0))
((0 . "LINE") (100 . "AcDbEntity") (8 . "MASONRY") (62 . 7) (370 . 13) (100 . "AcDbLine") (10 15124.4343891403
2526.3949434389 0.0) (11 15124.4343891403 2552.7905769231 0.0))
((0 . "LINE") (100 . "AcDbEntity") (8 . "MASONRY") (62 . 7) (370 . 13) (100 . "AcDbLine") (10 15124.4343891403
2526.3949434389 0.0) (11 15331.8268778281 2526.3949434389 0.0))
((0 . "LINE") (100 . "AcDbEntity") (8 . "MASONRY") (62 . 7) (370 . 13) (100 . "AcDbLine") (10 15146.2938122172
475.3057579186 0.0) (11 15146.2938122172 520.3619909502 0.0))
((0 . "LINE") (100 . "AcDbEntity") (8 . "MASONRY") (62 . 7) (370 . 13) (100 . "AcDbLine") (10 15256.4084162896
2631.9760972851 0.0) (11 15256.4084162896 2662.1415497738 0.0))
((0 . "LINE") (100 . "AcDbEntity") (8 . "MASONRY") (62 . 7) (370 . 13) (100 . "AcDbLine") (10 15256.4084162896
2662.1415497738 0.0) (11 15541.1001357466 2662.1415497738 0.0))
((0 . "LINE") (100 . "AcDbEntity") (8 . "MASONRY") (62 . 7) (370 . 13) (100 . "AcDbLine") (10 15256.4084162896
2631.9760972851 0.0) (11 15426.0916742081 2631.9760972851 0.0))
((0 . "LINE") (100 . "AcDbEntity") (8 . "MASONRY") (62 . 7) (370 . 13) (100 . "AcDbLine") (10 15460.0283257919
2560.3315950226 0.0) (11 15429.8642533937 2560.3315950226 0.0))
((0 . "LINE") (100 . "AcDbEntity") (8 . "MASONRY") (62 . 7) (370 . 13) (100 . "AcDbLine") (10 15429.8642533937
2560.3315950226 0.0) (11 15263.9535746606 2560.3315950226 0.0))
((0 . "LINE") (100 . "AcDbEntity") (8 . "MASONRY") (62 . 7) (370 . 13) (100 . "AcDbLine") (10 15308.4622850679
2239.8190045249 0.0) (11 15308.4622850679 2233.9005316742 0.0))
((0 . "LINE") (100 . "AcDbEntity") (8 . "MASONRY") (62 . 7) (370 . 13) (100 . "AcDbLine") (10 15308.4622850679
2239.8190045249 0.0) (11 15377.0757466063 2239.8190045249 0.0))
((0 . "LINE") (100 . "AcDbEntity") (8 . "MASONRY") (62 . 7) (370 . 13) (100 . "AcDbLine") (10 15312.9695022624
2390.6490271493 0.0) (11 15426.0916742081 2390.6490271493 0.0))
((0 . "LINE") (100 . "AcDbEntity") (8 . "MASONRY") (62 . 7) (370 . 13) (100 . "AcDbLine") (10 15346.9061538462
2526.3949434389 0.0) (11 15460.0283257919 2526.3949434389 0.0))
((0 . "LINE") (100 . "AcDbEntity") (8 . "MASONRY") (62 . 7) (370 . 13) (100 . "AcDbLine") (10 15433.6368325792
565.5169570136 0.0) (11 15433.6368325792 538.3579524887 0.0))
((0 . "LINE") (100 . "AcDbEntity") (8 . "MASONRY") (62 . 7) (370 . 13) (100 . "AcDbLine") (10 15754.1556334842
565.5169570136 0.0) (11 15493.9649773756 565.5169570136 0.0))
((0 . "LINE") (100 . "AcDbEntity") (8 . "MASONRY") (62 . 7) (370 . 13) (100 . "AcDbLine") (10 15493.9649773756
565.5169570136 0.0) (11 15433.6368325792 565.5169570136 0.0))
((0 . "LINE") (100 . "AcDbEntity") (8 . "MASONRY") (62 . 7) (370 . 13) (100 . "AcDbLine") (10 15493.9649773756
2631.9760972851 0.0) (11 15437.4038914027 2631.9760972851 0.0))
((0 . "LINE") (100 . "AcDbEntity") (8 . "MASONRY") (62 . 7) (370 . 13) (100 . "AcDbLine") (10 15463.8009049774
2394.4195361991 0.0) (11 15456.2612669683 2394.4195361991 0.0))
((0 . "LINE") (100 . "AcDbEntity") (8 . "MASONRY") (62 . 7) (370 . 13) (100 . "AcDbLine") (10 15460.0283257919
2439.6684049774 0.0) (11 15460.0283257919 2526.3949434389 0.0))
((0 . "LINE") (100 . "AcDbEntity") (8 . "MASONRY") (62 . 7) (370 . 13) (100 . "AcDbLine") (10 15460.0283257919
2560.3315950226 0.0) (11 15460.0283257919 2526.3949434389 0.0))
((0 . "LINE") (100 . "AcDbEntity") (8 . "MASONRY") (62 . 7) (370 . 13) (100 . "AcDbLine") (10 15460.0283257919
2560.3315950226 0.0) (11 15799.394841629 2560.3315950226 0.0))
((0 . "LINE") (100 . "AcDbEntity") (8 . "MASONRY") (62 . 7) (370 . 13) (100 . "AcDbLine") (10 15799.394841629
2560.3315950226 0.0) (11 15810.6297285068 2560.3315950226 0.0))
((0 . "LINE") (100 . "AcDbEntity") (8 . "MASONRY") (62 . 7) (370 . 13) (100 . "AcDbLine") (10 15810.6297285068
2560.3315950226 0.0) (11 15810.6297285068 2488.6877828054 0.0))
((0 . "LINE") (100 . "AcDbEntity") (8 . "MASONRY") (62 . 7) (370 . 13) (100 . "AcDbLine") (10 15501.5101357466
2315.2340158371 0.0) (11 15720.209321267 2315.2340158371 0.0))
((0 . "LINE") (100 . "AcDbEntity") (8 . "MASONRY") (62 . 7) (370 . 13) (100 . "AcDbLine") (10 15678.7330316742
2398.1900452489 0.0) (11 15588.2352941176 2398.1900452489 0.0))
((0 . "LINE") (100 . "AcDbEntity") (8 . "MASONRY") (62 . 7) (370 . 13) (100 . "AcDbLine") (10 15588.2352941176
2398.1900452489 0.0) (11 15509.0497737557 2398.1900452489 0.0))
((0 . "LINE") (100 . "AcDbEntity") (8 . "MASONRY") (62 . 7) (370 . 13) (100 . "AcDbLine") (10 15512.8223529412
2530.1661425339 0.0) (11 15765.4581900453 2530.1661425339 0.0))
((0 . "LINE") (100 . "AcDbEntity") (8 . "MASONRY") (62 . 7) (370 . 13) (100 . "AcDbLine") (10 15529.4054072398
516.5921719457 0.0) (11 15529.4054072398 499.1798868778 0.0))
((0 . "LINE") (100 . "AcDbEntity") (8 . "MASONRY") (62 . 7) (370 . 13) (100 . "AcDbLine") (10 15541.1001357466
2662.1415497738 0.0) (11 15541.1001357466 2639.5171153846 0.0))
((0 . "LINE") (100 . "AcDbEntity") (8 . "MASONRY") (62 . 7) (370 . 13) (100 . "AcDbLine") (10 15541.1001357466
2662.1415497738 0.0) (11 15686.2726696833 2662.1415497738 0.0))
((0 . "LINE") (100 . "AcDbEntity") (8 . "MASONRY") (62 . 7) (370 . 13) (100 . "AcDbLine") (10 15591.8311199095
476.2637895928 0.0) (11 15591.8311199095 486.4253393665 0.0))
((0 . "LINE") (100 . "AcDbEntity") (8 . "MASONRY") (62 . 7) (370 . 13) (100 . "AcDbLine") (10 15599.5475113122
2633.8616968326 0.0) (11 15682.5056108597 2633.8616968326 0.0))
((0 . "LINE") (100 . "AcDbEntity") (8 . "MASONRY") (62 . 7) (370 . 13) (100 . "AcDbLine") (10 15723.9819004525
1159.2965158371 0.0) (11 15713.6262217195 1159.2965158371 0.0))
((0 . "LINE") (100 . "AcDbEntity") (8 . "MASONRY") (62 . 7) (370 . 13) (100 . "AcDbLine") (10 15760.8584615385
1121.4616176471 0.0) (11 15788.0826244344 1121.4616176471 0.0))
((0 . "LINE") (100 . "AcDbEntity") (8 . "MASONRY") (62 . 7) (370 . 13) (100 . "AcDbLine") (10 15716.4422624434
2394.4195361991 0.0) (11 15697.5848868778 2394.4195361991 0.0))
((0 . "LINE") (100 . "AcDbEntity") (8 . "MASONRY") (62 . 7) (370 . 13) (100 . "AcDbLine") (10 15696.3034276018
509.6949208145 0.0) (11 15696.3034276018 527.9043891403 0.0))
((0 . "LINE") (100 . "AcDbEntity") (8 . "MASONRY") (62 . 7) (370 . 13) (100 . "AcDbLine") (10 15716.4422624434
2349.1706674208 0.0) (11 15716.4422624434 2394.4195361991 0.0))
((0 . "LINE") (100 . "AcDbEntity") (8 . "MASONRY") (62 . 7) (370 . 13) (100 . "AcDbLine") (10 15931.3743891403
2394.4195361991 0.0) (11 15716.4422624434 2394.4195361991 0.0))
((0 . "LINE") (100 . "AcDbEntity") (8 . "MASONRY") (62 . 7) (370 . 13) (100 . "AcDbLine") (10 15731.5215384615
2266.2139479638 0.0) (11 15716.4422624434 2266.2139479638 0.0))
((0 . "LINE") (100 . "AcDbEntity") (8 . "MASONRY") (62 . 7) (370 . 13) (100 . "AcDbLine") (10 15720.209321267
2664.0271493213 0.0) (11 15731.5215384615 2664.0271493213 0.0))
((0 . "LINE") (100 . "AcDbEntity") (8 . "MASONRY") (62 . 7) (370 . 13) (100 . "AcDbLine") (10 15720.209321267
2300.1505995475 0.0) (11 15720.209321267 2315.2340158371 0.0))
((0 . "LINE") (100 . "AcDbEntity") (8 . "MASONRY") (62 . 7) (370 . 13) (100 . "AcDbLine") (10 15765.4581900453
2315.2340158371 0.0) (11 15720.209321267 2315.2340158371 0.0))
((0 . "LINE") (100 . "AcDbEntity") (8 . "MASONRY") (62 . 7) (370 . 13) (100 . "AcDbLine") (10 15801.2797511312
2115.3846153846 0.0) (11 15801.2797511312 2078.2795248869 0.0))
((0 . "LINE") (100 . "AcDbEntity") (8 . "MASONRY") (62 . 7) (370 . 13) (100 . "AcDbLine") (10 15801.2797511312
2078.2795248869 0.0) (11 15720.209321267 2078.2795248869 0.0))
((0 . "LINE") (100 . "AcDbEntity") (8 . "MASONRY") (62 . 7) (370 . 13) (100 . "AcDbLine") (10 15799.394841629
1255.6561085973 0.0) (11 15720.209321267 1255.6561085973 0.0))
((0 . "LINE") (100 . "AcDbEntity") (8 . "MASONRY") (62 . 7) (370 . 13) (100 . "AcDbLine") (10 15723.9819004525
2030.6907466063 0.0) (11 15846.53 2030.6907466063 0.0))
((0 . "LINE") (100 . "AcDbEntity") (8 . "MASONRY") (62 . 7) (370 . 13) (100 . "AcDbLine") (10 15723.9819004525
1670.4383257919 0.0) (11 15818.2522171946 1670.4383257919 0.0))
((0 . "LINE") (100 . "AcDbEntity") (8 . "MASONRY") (62 . 7) (370 . 13) (100 . "AcDbLine") (10 15791.8552036199
1285.821561086 0.0) (11 15723.9819004525 1285.821561086 0.0))
((0 . "LINE") (100 . "AcDbEntity") (8 . "MASONRY") (62 . 7) (370 . 13) (100 . "AcDbLine") (10 15846.53 1904.2229977376
0.0) (11 15727.754479638 1904.2229977376 0.0))
((0 . "LINE") (100 . "AcDbEntity") (8 . "MASONRY") (62 . 7) (370 . 13) (100 . "AcDbLine") (10 15765.4581900453
1513.9521945701 0.0) (11 15727.754479638 1513.9521945701 0.0))
((0 . "LINE") (100 . "AcDbEntity") (8 . "MASONRY") (62 . 7) (370 . 13) (100 . "AcDbLine") (10 15727.754479638
1331.0704298643 0.0) (11 15852.1888687783 1331.0704298643 0.0))
((0 . "LINE") (100 . "AcDbEntity") (8 . "MASONRY") (62 . 7) (370 . 13) (100 . "AcDbLine") (10 15731.5215384615
1459.2760180995 0.0) (11 15761.6911312217 1459.2760180995 0.0))
((0 . "LINE") (100 . "AcDbEntity") (8 . "MASONRY") (62 . 7) (370 . 13) (100 . "AcDbLine") (10 15757.9185520362
2631.9754072398 0.0) (11 15739.0666968326 2631.9754072398 0.0))
((0 . "LINE") (100 . "AcDbEntity") (8 . "MASONRY") (62 . 7) (370 . 13) (100 . "AcDbLine") (10 15754.1459728507
2263.6524095023 0.0) (11 16140.6476470588 2263.6524095023 0.0))
((0 . "LINE") (100 . "AcDbEntity") (8 . "MASONRY") (62 . 7) (370 . 13) (100 . "AcDbLine") (10 16150.0735746606
2641.4027149321 0.0) (11 16089.7454298643 2641.4027149321 0.0))
((0 . "LINE") (100 . "AcDbEntity") (8 . "MASONRY") (62 . 7) (370 . 13) (100 . "AcDbLine") (10 16089.7454298643
2641.4027149321 0.0) (11 15765.4581900453 2641.4027149321 0.0))
((0 . "LINE") (100 . "AcDbEntity") (8 . "MASONRY") (62 . 7) (370 . 13) (100 . "AcDbLine") (10 15780.5429864253
1459.2760180995 0.0) (11 15806.94 1459.2760180995 0.0))
((0 . "LINE") (100 . "AcDbEntity") (8 . "MASONRY") (62 . 7) (370 . 13) (100 . "AcDbLine") (10 15806.94 1541.0341289593
0.0) (11 15791.8552036199 1541.0341289593 0.0))
((0 . "LINE") (100 . "AcDbEntity") (8 . "MASONRY") (62 . 7) (370 . 13) (100 . "AcDbLine") (10 15804.7112556561
2239.8190045249 0.0) (11 15804.7112556561 2168.3595361991 0.0))
((0 . "LINE") (100 . "AcDbEntity") (8 . "MASONRY") (62 . 7) (370 . 13) (100 . "AcDbLine") (10 15804.7112556561
2168.3595361991 0.0) (11 15933.257918552 2168.3595361991 0.0))
((0 . "LINE") (100 . "AcDbEntity") (8 . "MASONRY") (62 . 7) (370 . 13) (100 . "AcDbLine") (10 15806.94 1421.5695475113
0.0) (11 15806.94 1459.2760180995 0.0))
((0 . "LINE") (100 . "AcDbEntity") (8 . "MASONRY") (62 . 7) (370 . 13) (100 . "AcDbLine") (10 15806.94 1476.2443438914
0.0) (11 15806.94 1459.2760180995 0.0))
((0 . "LINE") (100 . "AcDbEntity") (8 . "MASONRY") (62 . 7) (370 . 13) (100 . "AcDbLine") (10 15808.8235294118
2477.3755656109 0.0) (11 15808.8235294118 2443.4389140271 0.0))
((0 . "LINE") (100 . "AcDbEntity") (8 . "MASONRY") (62 . 7) (370 . 13) (100 . "AcDbLine") (10 15806.94 1476.2443438914
0.0) (11 15806.94 1541.0341289593 0.0))
((0 . "LINE") (100 . "AcDbEntity") (8 . "MASONRY") (62 . 7) (370 . 13) (100 . "AcDbLine") (10 16206.6374208145
1541.0341289593 0.0) (11 16059.5758371041 1541.0341289593 0.0))
((0 . "LINE") (100 . "AcDbEntity") (8 . "MASONRY") (62 . 7) (370 . 13) (100 . "AcDbLine") (10 16059.5758371041
1541.0341289593 0.0) (11 16025.6350452489 1541.0341289593 0.0))
((0 . "LINE") (100 . "AcDbEntity") (8 . "MASONRY") (62 . 7) (370 . 13) (100 . "AcDbLine") (10 16025.6350452489
1541.0341289593 0.0) (11 15806.94 1541.0341289593 0.0))
((0 . "LINE") (100 . "AcDbEntity") (8 . "MASONRY") (62 . 7) (370 . 13) (100 . "AcDbLine") (10 15814.4796380091
2590.4977375566 0.0) (11 15814.4796380091 2605.5804638009 0.0))
((0 . "LINE") (100 . "AcDbEntity") (8 . "MASONRY") (62 . 7) (370 . 13) (100 . "AcDbLine") (10 15806.94 1476.2443438914
0.0) (11 15825.7918552036 1476.2443438914 0.0))
((0 . "LINE") (100 . "AcDbEntity") (8 . "MASONRY") (62 . 7) (370 . 13) (100 . "AcDbLine") (10 15814.4796380091
1817.3417986425 0.0) (11 15829.5644343891 1817.3417986425 0.0))
((0 . "LINE") (100 . "AcDbEntity") (8 . "MASONRY") (62 . 7) (370 . 13) (100 . "AcDbLine") (10 15829.5644343891
1817.3417986425 0.0) (11 16037.5562330317 1817.3417986425 0.0))
((0 . "LINE") (100 . "AcDbEntity") (8 . "MASONRY") (62 . 7) (370 . 13) (100 . "AcDbLine") (10 16037.5562330317
1817.3417986425 0.0) (11 16037.5562330317 1866.5158371041 0.0))
((0 . "LINE") (100 . "AcDbEntity") (8 . "MASONRY") (62 . 7) (370 . 13) (100 . "AcDbLine") (10 16037.5562330317
1866.5158371041 0.0) (11 16063.3456561086 1866.5158371041 0.0))
((0 . "LINE") (100 . "AcDbEntity") (8 . "MASONRY") (62 . 7) (370 . 13) (100 . "AcDbLine") (10 15816.3659276018
1745.8512669683 0.0) (11 15816.3659276018 1768.4757013575 0.0))
((0 . "LINE") (100 . "AcDbEntity") (8 . "MASONRY") (62 . 7) (370 . 13) (100 . "AcDbLine") (10 15818.2522171946
1719.4570135747 0.0) (11 15818.2522171946 1670.4383257919 0.0))
((0 . "LINE") (100 . "AcDbEntity") (8 . "MASONRY") (62 . 7) (370 . 13) (100 . "AcDbLine") (10 16029.4117647059
1670.4383257919 0.0) (11 15818.2522171946 1670.4383257919 0.0))
((0 . "LINE") (100 . "AcDbEntity") (8 . "MASONRY") (62 . 7) (370 . 13) (100 . "AcDbLine") (10 15816.8961877828
1248.1137104072 0.0) (11 15816.8961877828 1274.5107239819 0.0))
((0 . "LINE") (100 . "AcDbEntity") (8 . "MASONRY") (62 . 7) (370 . 13) (100 . "AcDbLine") (10 15816.8961877828
1274.5107239819 0.0) (11 15829.5644343891 1274.5107239819 0.0))
((0 . "LINE") (100 . "AcDbEntity") (8 . "MASONRY") (62 . 7) (370 . 13) (100 . "AcDbLine") (10 15829.5644343891
1289.592760181 0.0) (11 15829.5644343891 1274.5107239819 0.0))
((0 . "LINE") (100 . "AcDbEntity") (8 . "MASONRY") (62 . 7) (370 . 13) (100 . "AcDbLine") (10 16508.2974660633
1274.5107239819 0.0) (11 15829.5644343891 1274.5107239819 0.0))
((0 . "LINE") (100 . "AcDbEntity") (8 . "MASONRY") (62 . 7) (370 . 13) (100 . "AcDbLine") (10 15837.1586199095
1024.5013348416 0.0) (11 15859.7285067873 1024.5013348416 0.0))
((0 . "LINE") (100 . "AcDbEntity") (8 . "MASONRY") (62 . 7) (370 . 13) (100 . "AcDbLine") (10 15833.3314932127
1084.086561086 0.0) (11 15844.6437104072 1084.086561086 0.0))
((0 . "LINE") (100 . "AcDbEntity") (8 . "MASONRY") (62 . 7) (370 . 13) (100 . "AcDbLine") (10 15963.4247511312
727.6778393665 0.0) (11 15893.665158371 727.6778393665 0.0))
((0 . "LINE") (100 . "AcDbEntity") (8 . "MASONRY") (62 . 7) (370 . 13) (100 . "AcDbLine") (10 15874.8133031674
1904.2229977376 0.0) (11 15846.53 1904.2229977376 0.0))
((0 . "LINE") (100 . "AcDbEntity") (8 . "MASONRY") (62 . 7) (370 . 13) (100 . "AcDbLine") (10 15846.53 1904.2229977376
0.0) (11 15846.53 2030.6907466063 0.0))
((0 . "LINE") (100 . "AcDbEntity") (8 . "MASONRY") (62 . 7) (370 . 13) (100 . "AcDbLine") (10 16074.6606334842
2030.6907466063 0.0) (11 15846.53 2030.6907466063 0.0))
((0 . "LINE") (100 . "AcDbEntity") (8 . "MASONRY") (62 . 7) (370 . 13) (100 . "AcDbLine") (10 16070.8880542986
1176.4705882353 0.0) (11 15848.4162895928 1176.4705882353 0.0))
((0 . "LINE") (100 . "AcDbEntity") (8 . "MASONRY") (62 . 7) (370 . 13) (100 . "AcDbLine") (10 15852.1888687783
2102.1874886878 0.0) (11 15882.3529411765 2102.1874886878 0.0))
((0 . "LINE") (100 . "AcDbEntity") (8 . "MASONRY") (62 . 7) (370 . 13) (100 . "AcDbLine") (10 15976.6232579186
957.7686425339 0.0) (11 15893.665158371 957.7686425339 0.0))
((0 . "LINE") (100 . "AcDbEntity") (8 . "MASONRY") (62 . 7) (370 . 13) (100 . "AcDbLine") (10 15863.5010859729
1093.5152488688 0.0) (11 15976.6232579186 1093.5152488688 0.0))
((0 . "LINE") (100 . "AcDbEntity") (8 . "MASONRY") (62 . 7) (370 . 13) (100 . "AcDbLine") (10 15867.2681447964
1334.8416289593 0.0) (11 15974.7369683258 1334.8416289593 0.0))
((0 . "LINE") (100 . "AcDbEntity") (8 . "MASONRY") (62 . 7) (370 . 13) (100 . "AcDbLine") (10 15893.665158371
863.4983257919 0.0) (11 15978.5067873303 863.4983257919 0.0))
((0 . "LINE") (100 . "AcDbEntity") (8 . "MASONRY") (62 . 7) (370 . 13) (100 . "AcDbLine") (10 15878.580361991
1749.6238461538 0.0) (11 15871.0407239819 1749.6238461538 0.0))
((0 . "LINE") (100 . "AcDbEntity") (8 . "MASONRY") (62 . 7) (370 . 13) (100 . "AcDbLine") (10 15871.0407239819
1380.0904977376 0.0) (11 15920.0621719457 1380.0904977376 0.0))
((0 . "LINE") (100 . "AcDbEntity") (8 . "MASONRY") (62 . 7) (370 . 13) (100 . "AcDbLine") (10 15883.3692760181
560.5673642534 0.0) (11 15883.3692760181 565.6108597285 0.0))
((0 . "LINE") (100 . "AcDbEntity") (8 . "MASONRY") (62 . 7) (370 . 13) (100 . "AcDbLine") (10 15889.8925791855
1902.33739819 0.0) (11 15923.8292307692 1902.33739819 0.0))
((0 . "LINE") (100 . "AcDbEntity") (8 . "MASONRY") (62 . 7) (370 . 13) (100 . "AcDbLine") (10 15901.2047963801
791.8552036199 0.0) (11 16327.3019909502 791.8552036199 0.0))
((0 . "LINE") (100 . "AcDbEntity") (8 . "MASONRY") (62 . 7) (370 . 13) (100 . "AcDbLine") (10 15933.257918552
2098.4162895928 0.0) (11 15920.0621719457 2098.4162895928 0.0))
((0 . "LINE") (100 . "AcDbEntity") (8 . "MASONRY") (62 . 7) (370 . 13) (100 . "AcDbLine") (10 15933.257918552
2098.4162895928 0.0) (11 16021.8721266968 2098.4162895928 0.0))
((0 . "LINE") (100 . "AcDbEntity") (8 . "MASONRY") (62 . 7) (370 . 13) (100 . "AcDbLine") (10 16021.8721266968
2098.4162895928 0.0) (11 16217.9468778281 2098.4162895928 0.0))
((0 . "LINE") (100 . "AcDbEntity") (8 . "MASONRY") (62 . 7) (370 . 13) (100 . "AcDbLine") (10 15933.257918552
2098.4162895928 0.0) (11 15933.257918552 2168.3595361991 0.0))
((0 . "LINE") (100 . "AcDbEntity") (8 . "MASONRY") (62 . 7) (370 . 13) (100 . "AcDbLine") (10 15927.6018099548
593.8914027149 0.0) (11 15952.1125339367 593.8914027149 0.0))
((0 . "LINE") (100 . "AcDbEntity") (8 . "MASONRY") (62 . 7) (370 . 13) (100 . "AcDbLine") (10 15938.9140271493
2439.6684049774 0.0) (11 15938.9140271493 2462.2928393665 0.0))
((0 . "LINE") (100 . "AcDbEntity") (8 . "MASONRY") (62 . 7) (370 . 13) (100 . "AcDbLine") (10 15931.3743891403
2394.4195361991 0.0) (11 15931.3743891403 2409.5022624434 0.0))
((0 . "LINE") (100 . "AcDbEntity") (8 . "MASONRY") (62 . 7) (370 . 13) (100 . "AcDbLine") (10 15931.3743891403
2394.4195361991 0.0) (11 16025.6391855204 2394.4195361991 0.0))
((0 . "LINE") (100 . "AcDbEntity") (8 . "MASONRY") (62 . 7) (370 . 13) (100 . "AcDbLine") (10 15965.311040724
2462.2928393665 0.0) (11 15938.9140271493 2462.2928393665 0.0))
((0 . "LINE") (100 . "AcDbEntity") (8 . "MASONRY") (62 . 7) (370 . 13) (100 . "AcDbLine") (10 16036.9514027149
2502.5663800905 0.0) (11 15938.9140271493 2502.5663800905 0.0))
((0 . "LINE") (100 . "AcDbEntity") (8 . "MASONRY") (62 . 7) (370 . 13) (100 . "AcDbLine") (10 15938.9140271493
2502.5663800905 0.0) (11 15938.9140271493 2462.2928393665 0.0))
((0 . "LINE") (100 . "AcDbEntity") (8 . "MASONRY") (62 . 7) (370 . 13) (100 . "AcDbLine") (10 15933.257918552
2168.3595361991 0.0) (11 16146.3810859729 2168.3595361991 0.0))
((0 . "LINE") (100 . "AcDbEntity") (8 . "MASONRY") (62 . 7) (370 . 13) (100 . "AcDbLine") (10 15938.9140271493
1896.5273190045 0.0) (11 15959.6521719457 1896.5273190045 0.0))
((0 . "LINE") (100 . "AcDbEntity") (8 . "MASONRY") (62 . 7) (370 . 13) (100 . "AcDbLine") (10 15974.7342081448
3240.526979638 0.0) (11 15974.7342081448 3580.3167420814 0.0))
((0 . "LINE") (100 . "AcDbEntity") (8 . "MASONRY") (62 . 7) (370 . 13) (100 . "AcDbLine") (10 15972.850678733
2760.1809954751 0.0) (11 15999.2476923077 2760.1809954751 0.0))
((0 . "LINE") (100 . "AcDbEntity") (8 . "MASONRY") (62 . 7) (370 . 13) (100 . "AcDbLine") (10 15967.1945701357
593.8914027149 0.0) (11 15952.1125339367 593.8914027149 0.0))
((0 . "LINE") (100 . "AcDbEntity") (8 . "MASONRY") (62 . 7) (370 . 13) (100 . "AcDbLine") (10 15952.1125339367
614.6295475113 0.0) (11 15952.1125339367 593.8914027149 0.0))
((0 . "LINE") (100 . "AcDbEntity") (8 . "MASONRY") (62 . 7) (370 . 13) (100 . "AcDbLine") (10 15959.6521719457
1896.5273190045 0.0) (11 15959.6521719457 1877.8280542986 0.0))
((0 . "LINE") (100 . "AcDbEntity") (8 . "MASONRY") (62 . 7) (370 . 13) (100 . "AcDbLine") (10 15959.6521719457
629.7143438914 0.0) (11 15959.6521719457 644.7963800905 0.0))
((0 . "LINE") (100 . "AcDbEntity") (8 . "MASONRY") (62 . 7) (370 . 13) (100 . "AcDbLine") (10 16063.3456561086
1866.5158371041 0.0) (11 16063.3456561086 1896.5273190045 0.0))
((0 . "LINE") (100 . "AcDbEntity") (8 . "MASONRY") (62 . 7) (370 . 13) (100 . "AcDbLine") (10 16063.3456561086
1896.5273190045 0.0) (11 15959.6521719457 1896.5273190045 0.0))
((0 . "LINE") (100 . "AcDbEntity") (8 . "MASONRY") (62 . 7) (370 . 13) (100 . "AcDbLine") (10 15963.4247511312
678.7330316742 0.0) (11 15963.4247511312 727.6778393665 0.0))
((0 . "LINE") (100 . "AcDbEntity") (8 . "MASONRY") (62 . 7) (370 . 13) (100 . "AcDbLine") (10 15963.4247511312
727.6778393665 0.0) (11 16282.0531221719 727.6778393665 0.0))
((0 . "LINE") (100 . "AcDbEntity") (8 . "MASONRY") (62 . 7) (370 . 13) (100 . "AcDbLine") (10 15967.1945701357
527.9043891403 0.0) (11 15967.1945701357 593.8914027149 0.0))
((0 . "LINE") (100 . "AcDbEntity") (8 . "MASONRY") (62 . 7) (370 . 13) (100 . "AcDbLine") (10 15967.1945701357
593.8914027149 0.0) (11 16142.5339366516 593.8914027149 0.0))
((0 . "LINE") (100 . "AcDbEntity") (8 . "MASONRY") (62 . 7) (370 . 13) (100 . "AcDbLine") (10 15974.7369683258
1470.5882352941 0.0) (11 15974.7369683258 1478.1306334842 0.0))
((0 . "LINE") (100 . "AcDbEntity") (8 . "MASONRY") (62 . 7) (370 . 13) (100 . "AcDbLine") (10 15974.7369683258
1376.320678733 0.0) (11 15974.7369683258 1334.8416289593 0.0))
((0 . "LINE") (100 . "AcDbEntity") (8 . "MASONRY") (62 . 7) (370 . 13) (100 . "AcDbLine") (10 16106.7109954751
1027.4495248869 0.0) (11 15999.2476923077 1027.4495248869 0.0))
((0 . "LINE") (100 . "AcDbEntity") (8 . "MASONRY") (62 . 7) (370 . 13) (100 . "AcDbLine") (10 15999.2476923077
1027.4495248869 0.0) (11 15971.566459276 1027.4495248869 0.0))
((0 . "LINE") (100 . "AcDbEntity") (8 . "MASONRY") (62 . 7) (370 . 13) (100 . "AcDbLine") (10 15971.566459276
1027.4495248869 0.0) (11 15971.566459276 999.2449321267 0.0))
((0 . "LINE") (100 . "AcDbEntity") (8 . "MASONRY") (62 . 7) (370 . 13) (100 . "AcDbLine") (10 15976.6232579186
1440.4214027149 0.0) (11 15976.6232579186 1414.0271493213 0.0))
((0 . "LINE") (100 . "AcDbEntity") (8 . "MASONRY") (62 . 7) (370 . 13) (100 . "AcDbLine") (10 16185.8965158371
1334.8416289593 0.0) (11 15974.7369683258 1334.8416289593 0.0))
((0 . "LINE") (100 . "AcDbEntity") (8 . "MASONRY") (62 . 7) (370 . 13) (100 . "AcDbLine") (10 15976.6232579186
1093.5152488688 0.0) (11 15976.6232579186 1067.1182352941 0.0))
((0 . "LINE") (100 . "AcDbEntity") (8 . "MASONRY") (62 . 7) (370 . 13) (100 . "AcDbLine") (10 15976.6232579186
1093.5152488688 0.0) (11 16088.5399208145 1093.5152488688 0.0))
((0 . "LINE") (100 . "AcDbEntity") (8 . "MASONRY") (62 . 7) (370 . 13) (100 . "AcDbLine") (10 16289.592760181
957.7686425339 0.0) (11 15976.6232579186 957.7686425339 0.0))
((0 . "LINE") (100 . "AcDbEntity") (8 . "MASONRY") (62 . 7) (370 . 13) (100 . "AcDbLine") (10 15976.6232579186
946.4564253394 0.0) (11 15976.6232579186 957.7686425339 0.0))
((0 . "LINE") (100 . "AcDbEntity") (8 . "MASONRY") (62 . 7) (370 . 13) (100 . "AcDbLine") (10 15978.5067873303
863.4983257919 0.0) (11 15978.5067873303 912.5197737557 0.0))
((0 . "LINE") (100 . "AcDbEntity") (8 . "MASONRY") (62 . 7) (370 . 13) (100 . "AcDbLine") (10 16070.8880542986
2850.6787330317 0.0) (11 16070.8880542986 2819.1524208145 0.0))
((0 . "LINE") (100 . "AcDbEntity") (8 . "MASONRY") (62 . 7) (370 . 13) (100 . "AcDbLine") (10 16070.8880542986
2819.1524208145 0.0) (11 15980.3903167421 2819.1524208145 0.0))
((0 . "LINE") (100 . "AcDbEntity") (8 . "MASONRY") (62 . 7) (370 . 13) (100 . "AcDbLine") (10 15980.3903167421
1749.6238461538 0.0) (11 15991.7025339367 1749.6238461538 0.0))
((0 . "LINE") (100 . "AcDbEntity") (8 . "MASONRY") (62 . 7) (370 . 13) (100 . "AcDbLine") (10 15978.5067873303
863.4983257919 0.0) (11 16010.5599095023 863.4983257919 0.0))
((0 . "LINE") (100 . "AcDbEntity") (8 . "MASONRY") (62 . 7) (370 . 13) (100 . "AcDbLine") (10 15999.2476923077
2760.1809954751 0.0) (11 15999.2476923077 2782.8054298643 0.0))
((0 . "LINE") (100 . "AcDbEntity") (8 . "MASONRY") (62 . 7) (370 . 13) (100 . "AcDbLine") (10 16067.1209954751
2760.1809954751 0.0) (11 15999.2476923077 2760.1809954751 0.0))
((0 . "LINE") (100 . "AcDbEntity") (8 . "MASONRY") (62 . 7) (370 . 13) (100 . "AcDbLine") (10 16003.0147511312
3186.2008597285 0.0) (11 16025.6391855204 3186.2008597285 0.0))
((0 . "LINE") (100 . "AcDbEntity") (8 . "MASONRY") (62 . 7) (370 . 13) (100 . "AcDbLine") (10 16025.6391855204
3186.2008597285 0.0) (11 16200.9813122172 3186.2008597285 0.0))
((0 . "LINE") (100 . "AcDbEntity") (8 . "MASONRY") (62 . 7) (370 . 13) (100 . "AcDbLine") (10 16006.7873303167
3129.7136538462 0.0) (11 16018.0995475113 3129.7136538462 0.0))
((0 . "LINE") (100 . "AcDbEntity") (8 . "MASONRY") (62 . 7) (370 . 13) (100 . "AcDbLine") (10 16018.0995475113
3129.7136538462 0.0) (11 16082.2002714932 3129.7136538462 0.0))
((0 . "LINE") (100 . "AcDbEntity") (8 . "MASONRY") (62 . 7) (370 . 13) (100 . "AcDbLine") (10 16010.5599095023
2450.9806221719 0.0) (11 16036.9514027149 2450.9806221719 0.0))
((0 . "LINE") (100 . "AcDbEntity") (8 . "MASONRY") (62 . 7) (370 . 13) (100 . "AcDbLine") (10 16014.3269683258
3042.9864253394 0.0) (11 16029.4117647059 3042.9864253394 0.0))
((0 . "LINE") (100 . "AcDbEntity") (8 . "MASONRY") (62 . 7) (370 . 13) (100 . "AcDbLine") (10 16023.7556561086
2311.4628167421 0.0) (11 16023.7556561086 2300.1505995475 0.0))
((0 . "LINE") (100 . "AcDbEntity") (8 . "MASONRY") (62 . 7) (370 . 13) (100 . "AcDbLine") (10 16172.6980090498
2971.3426131222 0.0) (11 16025.6391855204 2971.3426131222 0.0))
((0 . "LINE") (100 . "AcDbEntity") (8 . "MASONRY") (62 . 7) (370 . 13) (100 . "AcDbLine") (10 16025.6391855204
2895.92760181 0.0) (11 16085.5226809955 2895.92760181 0.0))
((0 . "LINE") (100 . "AcDbEntity") (8 . "MASONRY") (62 . 7) (370 . 13) (100 . "AcDbLine") (10 16085.5226809955
2895.92760181 0.0) (11 16342.3812669683 2895.92760181 0.0))
((0 . "LINE") (100 . "AcDbEntity") (8 . "MASONRY") (62 . 7) (370 . 13) (100 . "AcDbLine") (10 16025.6391855204
2349.1706674208 0.0) (11 16025.6391855204 2394.4195361991 0.0))
((0 . "LINE") (100 . "AcDbEntity") (8 . "MASONRY") (62 . 7) (370 . 13) (100 . "AcDbLine") (10 16138.7613574661
2394.4195361991 0.0) (11 16025.6391855204 2394.4195361991 0.0))
((0 . "LINE") (100 . "AcDbEntity") (8 . "MASONRY") (62 . 7) (370 . 13) (100 . "AcDbLine") (10 16078.4332126697
1419.6832579186 0.0) (11 16025.6391855204 1419.6832579186 0.0))
((0 . "LINE") (100 . "AcDbEntity") (8 . "MASONRY") (62 . 7) (370 . 13) (100 . "AcDbLine") (10 16029.4117647059
3470.9657692308 0.0) (11 16085.9728506787 3470.9657692308 0.0))
((0 . "LINE") (100 . "AcDbEntity") (8 . "MASONRY") (62 . 7) (370 . 13) (100 . "AcDbLine") (10 16029.4117647059
1670.4383257919 0.0) (11 16214.1798190045 1670.4383257919 0.0))
((0 . "LINE") (100 . "AcDbEntity") (8 . "MASONRY") (62 . 7) (370 . 13) (100 . "AcDbLine") (10 16029.4117647059
1670.4383257919 0.0) (11 16029.4117647059 1640.2714932127 0.0))
((0 . "LINE") (100 . "AcDbEntity") (8 . "MASONRY") (62 . 7) (370 . 13) (100 . "AcDbLine") (10 16059.5758371041
3536.9534728507 0.0) (11 16033.1843438914 3536.9534728507 0.0))
((0 . "LINE") (100 . "AcDbEntity") (8 . "MASONRY") (62 . 7) (370 . 13) (100 . "AcDbLine") (10 16127.4491402715
1606.334841629 0.0) (11 16033.1843438914 1606.334841629 0.0))
((0 . "LINE") (100 . "AcDbEntity") (8 . "MASONRY") (62 . 7) (370 . 13) (100 . "AcDbLine") (10 16059.5758371041
857.8435972851 0.0) (11 16033.1843438914 857.8435972851 0.0))
((0 . "LINE") (100 . "AcDbEntity") (8 . "MASONRY") (62 . 7) (370 . 13) (100 . "AcDbLine") (10 16036.9514027149
3337.1040723982 0.0) (11 16199.0950226244 3337.1040723982 0.0))
((0 . "LINE") (100 . "AcDbEntity") (8 . "MASONRY") (62 . 7) (370 . 13) (100 . "AcDbLine") (10 16036.9514027149
2502.5663800905 0.0) (11 16036.9514027149 2450.9806221719 0.0))
((0 . "LINE") (100 . "AcDbEntity") (8 . "MASONRY") (62 . 7) (370 . 13) (100 . "AcDbLine") (10 16089.7454298643
2502.5663800905 0.0) (11 16036.9514027149 2502.5663800905 0.0))
((0 . "LINE") (100 . "AcDbEntity") (8 . "MASONRY") (62 . 7) (370 . 13) (100 . "AcDbLine") (10 16055.8087782805
2450.9806221719 0.0) (11 16036.9514027149 2450.9806221719 0.0))
((0 . "LINE") (100 . "AcDbEntity") (8 . "MASONRY") (62 . 7) (370 . 13) (100 . "AcDbLine") (10 16153.8461538462
3267.3458597285 0.0) (11 16040.7239819005 3267.3458597285 0.0))
((0 . "LINE") (100 . "AcDbEntity") (8 . "MASONRY") (62 . 7) (370 . 13) (100 . "AcDbLine") (10 16044.493800905
1738.3116289593 0.0) (11 16044.493800905 1768.4757013575 0.0))
((0 . "LINE") (100 . "AcDbEntity") (8 . "MASONRY") (62 . 7) (370 . 13) (100 . "AcDbLine") (10 16061.4621266968
769.2307692308 0.0) (11 16061.4621266968 761.6883710407 0.0))
((0 . "LINE") (100 . "AcDbEntity") (8 . "MASONRY") (62 . 7) (370 . 13) (100 . "AcDbLine") (10 16270.7409049774
3044.8713348416 0.0) (11 16067.1209954751 3044.8713348416 0.0))
((0 . "LINE") (100 . "AcDbEntity") (8 . "MASONRY") (62 . 7) (370 . 13) (100 . "AcDbLine") (10 16067.1209954751
2760.1809954751 0.0) (11 16067.1209954751 2771.4932126697 0.0))
((0 . "LINE") (100 . "AcDbEntity") (8 . "MASONRY") (62 . 7) (370 . 13) (100 . "AcDbLine") (10 16342.3812669683
2760.1809954751 0.0) (11 16067.1209954751 2760.1809954751 0.0))
((0 . "LINE") (100 . "AcDbEntity") (8 . "MASONRY") (62 . 7) (370 . 13) (100 . "AcDbLine") (10 16184.0102262443
1866.5158371041 0.0) (11 16063.3456561086 1866.5158371041 0.0))
((0 . "LINE") (100 . "AcDbEntity") (8 . "MASONRY") (62 . 7) (370 . 13) (100 . "AcDbLine") (10 16070.8880542986
1176.4705882353 0.0) (11 16070.8880542986 1184.0129864253 0.0))
((0 . "LINE") (100 . "AcDbEntity") (8 . "MASONRY") (62 . 7) (370 . 13) (100 . "AcDbLine") (10 16070.8880542986
1176.4705882353 0.0) (11 16088.5399208145 1176.4705882353 0.0))
((0 . "LINE") (100 . "AcDbEntity") (8 . "MASONRY") (62 . 7) (370 . 13) (100 . "AcDbLine") (10 16088.5399208145
1176.4705882353 0.0) (11 16088.5399208145 1131.221719457 0.0))
((0 . "LINE") (100 . "AcDbEntity") (8 . "MASONRY") (62 . 7) (370 . 13) (100 . "AcDbLine") (10 16074.6606334842
2030.6907466063 0.0) (11 16074.6606334842 2021.1163687783 0.0))
((0 . "LINE") (100 . "AcDbEntity") (8 . "MASONRY") (62 . 7) (370 . 13) (100 . "AcDbLine") (10 16102.9411764706
2030.6907466063 0.0) (11 16074.6606334842 2030.6907466063 0.0))
((0 . "LINE") (100 . "AcDbEntity") (8 . "MASONRY") (62 . 7) (370 . 13) (100 . "AcDbLine") (10 16078.4332126697
1932.5042307692 0.0) (11 16104.8247058824 1932.5042307692 0.0))
((0 . "LINE") (100 . "AcDbEntity") (8 . "MASONRY") (62 . 7) (370 . 13) (100 . "AcDbLine") (10 16082.2002714932
3080.6935859729 0.0) (11 16082.2002714932 3088.2352941176 0.0))
((0 . "LINE") (100 . "AcDbEntity") (8 . "MASONRY") (62 . 7) (370 . 13) (100 . "AcDbLine") (10 16112.3698642534
1987.1797171946 0.0) (11 16082.2002714932 1987.1797171946 0.0))
((0 . "LINE") (100 . "AcDbEntity") (8 . "MASONRY") (62 . 7) (370 . 13) (100 . "AcDbLine") (10 16312.2171945701
1093.5152488688 0.0) (11 16115.4575226244 1093.5152488688 0.0))
((0 . "LINE") (100 . "AcDbEntity") (8 . "MASONRY") (62 . 7) (370 . 13) (100 . "AcDbLine") (10 16115.4575226244
1093.5152488688 0.0) (11 16088.5399208145 1093.5152488688 0.0))
((0 . "LINE") (100 . "AcDbEntity") (8 . "MASONRY") (62 . 7) (370 . 13) (100 . "AcDbLine") (10 16088.5399208145
1093.5152488688 0.0) (11 16088.5399208145 1131.221719457 0.0))
((0 . "LINE") (100 . "AcDbEntity") (8 . "MASONRY") (62 . 7) (370 . 13) (100 . "AcDbLine") (10 16168.9309502262
1131.221719457 0.0) (11 16088.5399208145 1131.221719457 0.0))
((0 . "LINE") (100 . "AcDbEntity") (8 . "MASONRY") (62 . 7) (370 . 13) (100 . "AcDbLine") (10 16093.5124886878
3536.9534728507 0.0) (11 16108.5972850679 3536.9534728507 0.0))
((0 . "LINE") (100 . "AcDbEntity") (8 . "MASONRY") (62 . 7) (370 . 13) (100 . "AcDbLine") (10 16191.5553846154
859.7285067873 0.0) (11 16093.5124886878 859.7285067873 0.0))
((0 . "LINE") (100 . "AcDbEntity") (8 . "MASONRY") (62 . 7) (370 . 13) (100 . "AcDbLine") (10 16691.1764705882
3469.0801696833 0.0) (11 16097.2850678733 3469.0801696833 0.0))
((0 . "LINE") (100 . "AcDbEntity") (8 . "MASONRY") (62 . 7) (370 . 13) (100 . "AcDbLine") (10 16097.2850678733
2579.1081900452 0.0) (11 16081.4463122172 2579.1081900452 0.0))
((0 . "LINE") (100 . "AcDbEntity") (8 . "MASONRY") (62 . 7) (370 . 13) (100 . "AcDbLine") (10 16081.4463122172
2579.1081900452 0.0) (11 16081.4463122172 2547.137918552 0.0))
((0 . "LINE") (100 . "AcDbEntity") (8 . "MASONRY") (62 . 7) (370 . 13) (100 . "AcDbLine") (10 16081.4463122172
2547.137918552 0.0) (11 16123.682081448 2547.137918552 0.0))
((0 . "LINE") (100 . "AcDbEntity") (8 . "MASONRY") (62 . 7) (370 . 13) (100 . "AcDbLine") (10 16208.5209502262
2030.6907466063 0.0) (11 16102.9411764706 2030.6907466063 0.0))
((0 . "LINE") (100 . "AcDbEntity") (8 . "MASONRY") (62 . 7) (370 . 13) (100 . "AcDbLine") (10 16102.9411764706
2051.281821267 0.0) (11 16102.9411764706 2030.6907466063 0.0))
((0 . "LINE") (100 . "AcDbEntity") (8 . "MASONRY") (62 . 7) (370 . 13) (100 . "AcDbLine") (10 16106.7109954751
1027.4495248869 0.0) (11 16112.3698642534 1027.4495248869 0.0))
((0 . "LINE") (100 . "AcDbEntity") (8 . "MASONRY") (62 . 7) (370 . 13) (100 . "AcDbLine") (10 16106.7109954751
1027.4495248869 0.0) (11 16106.7109954751 1040.7239819005 0.0))
((0 . "LINE") (100 . "AcDbEntity") (8 . "MASONRY") (62 . 7) (370 . 13) (100 . "AcDbLine") (10 16293.3653393665
2505.6561085973 0.0) (11 16112.3698642534 2505.6561085973 0.0))
((0 . "LINE") (100 . "AcDbEntity") (8 . "MASONRY") (62 . 7) (370 . 13) (100 . "AcDbLine") (10 16112.3698642534
1972.096300905 0.0) (11 16112.3698642534 1987.1797171946 0.0))
((0 . "LINE") (100 . "AcDbEntity") (8 . "MASONRY") (62 . 7) (370 . 13) (100 . "AcDbLine") (10 16112.3698642534
1987.1797171946 0.0) (11 16208.5209502262 1987.1797171946 0.0))
((0 . "LINE") (100 . "AcDbEntity") (8 . "MASONRY") (62 . 7) (370 . 13) (100 . "AcDbLine") (10 16112.3698642534
1180.2404072398 0.0) (11 16242.5349321267 1180.2404072398 0.0))
((0 . "LINE") (100 . "AcDbEntity") (8 . "MASONRY") (62 . 7) (370 . 13) (100 . "AcDbLine") (10 16140.6476470588
2239.8190045249 0.0) (11 16140.6476470588 2263.6524095023 0.0))
((0 . "LINE") (100 . "AcDbEntity") (8 . "MASONRY") (62 . 7) (370 . 13) (100 . "AcDbLine") (10 16140.6476470588
2263.6524095023 0.0) (11 16440.4241628959 2263.6524095023 0.0))
((0 . "LINE") (100 . "AcDbEntity") (8 . "MASONRY") (62 . 7) (370 . 13) (100 . "AcDbLine") (10 16195.3224434389
2168.3595361991 0.0) (11 16146.3810859729 2168.3595361991 0.0))
((0 . "LINE") (100 . "AcDbEntity") (8 . "MASONRY") (62 . 7) (370 . 13) (100 . "AcDbLine") (10 16217.9496380091
2190.1975565611 0.0) (11 16172.6980090498 2190.1975565611 0.0))
((0 . "LINE") (100 . "AcDbEntity") (8 . "MASONRY") (62 . 7) (370 . 13) (100 . "AcDbLine") (10 16172.6980090498
2190.1975565611 0.0) (11 16146.3810859729 2190.1975565611 0.0))
((0 . "LINE") (100 . "AcDbEntity") (8 . "MASONRY") (62 . 7) (370 . 13) (100 . "AcDbLine") (10 16146.3810859729
2190.1975565611 0.0) (11 16146.3810859729 2168.3595361991 0.0))
((0 . "LINE") (100 . "AcDbEntity") (8 . "MASONRY") (62 . 7) (370 . 13) (100 . "AcDbLine") (10 16150.0735746606
2641.4027149321 0.0) (11 16150.0735746606 2722.4738348416 0.0))
((0 . "LINE") (100 . "AcDbEntity") (8 . "MASONRY") (62 . 7) (370 . 13) (100 . "AcDbLine") (10 16150.0735746606
2641.4027149321 0.0) (11 16315.9842533937 2641.4027149321 0.0))
((0 . "LINE") (100 . "AcDbEntity") (8 . "MASONRY") (62 . 7) (370 . 13) (100 . "AcDbLine") (10 16315.9842533937
2641.4027149321 0.0) (11 16315.9842533937 2665.9127488688 0.0))
((0 . "LINE") (100 . "AcDbEntity") (8 . "MASONRY") (62 . 7) (370 . 13) (100 . "AcDbLine") (10 16150.0735746606
2599.9250452489 0.0) (11 16293.3653393665 2599.9250452489 0.0))
((0 . "LINE") (100 . "AcDbEntity") (8 . "MASONRY") (62 . 7) (370 . 13) (100 . "AcDbLine") (10 16176.4705882353
2396.3051357466 0.0) (11 16153.8461538462 2396.3051357466 0.0))
((0 . "LINE") (100 . "AcDbEntity") (8 . "MASONRY") (62 . 7) (370 . 13) (100 . "AcDbLine") (10 16185.8965158371
1334.8416289593 0.0) (11 16195.3224434389 1334.8416289593 0.0))
((0 . "LINE") (100 . "AcDbEntity") (8 . "MASONRY") (62 . 7) (370 . 13) (100 . "AcDbLine") (10 16185.8965158371
1334.8416289593 0.0) (11 16185.8965158371 1346.1538461538 0.0))
((0 . "LINE") (100 . "AcDbEntity") (8 . "MASONRY") (62 . 7) (370 . 13) (100 . "AcDbLine") (10 16187.7828054299
1421.5695475113 0.0) (11 16221.7194570136 1421.5695475113 0.0))
((0 . "LINE") (100 . "AcDbEntity") (8 . "MASONRY") (62 . 7) (370 . 13) (100 . "AcDbLine") (10 16187.7828054299
1121.7957918552 0.0) (11 16214.1798190045 1121.7957918552 0.0))
((0 . "LINE") (100 . "AcDbEntity") (8 . "MASONRY") (62 . 7) (370 . 13) (100 . "AcDbLine") (10 16199.0950226244
3267.3458597285 0.0) (11 16191.5553846154 3267.3458597285 0.0))
((0 . "LINE") (100 . "AcDbEntity") (8 . "MASONRY") (62 . 7) (370 . 13) (100 . "AcDbLine") (10 16191.5553846154
859.7285067873 0.0) (11 16304.6775565611 859.7285067873 0.0))
((0 . "LINE") (100 . "AcDbEntity") (8 . "MASONRY") (62 . 7) (370 . 13) (100 . "AcDbLine") (10 16191.5553846154
859.7285067873 0.0) (11 16191.5553846154 829.5616742081 0.0))
((0 . "LINE") (100 . "AcDbEntity") (8 . "MASONRY") (62 . 7) (370 . 13) (100 . "AcDbLine") (10 16199.0950226244
3267.3458597285 0.0) (11 16199.0950226244 3299.3969117647 0.0))
((0 . "LINE") (100 . "AcDbEntity") (8 . "MASONRY") (62 . 7) (370 . 13) (100 . "AcDbLine") (10 16199.0950226244
3267.3458597285 0.0) (11 16199.0950226244 3254.1480429864 0.0))
((0 . "LINE") (100 . "AcDbEntity") (8 . "MASONRY") (62 . 7) (370 . 13) (100 . "AcDbLine") (10 16199.0950226244
3254.1480429864 0.0) (11 16199.0950226244 3220.2113914027 0.0))
((0 . "LINE") (100 . "AcDbEntity") (8 . "MASONRY") (62 . 7) (370 . 13) (100 . "AcDbLine") (10 16200.9813122172
3205.1279751131 0.0) (11 16200.9813122172 3186.2008597285 0.0))
((0 . "LINE") (100 . "AcDbEntity") (8 . "MASONRY") (62 . 7) (370 . 13) (100 . "AcDbLine") (10 16199.0950226244
1604.4499321267 0.0) (11 16342.3812669683 1604.4499321267 0.0))
((0 . "LINE") (100 . "AcDbEntity") (8 . "MASONRY") (62 . 7) (370 . 13) (100 . "AcDbLine") (10 16210.407239819
3386.1234502262 0.0) (11 16210.407239819 3408.7478846154 0.0))
((0 . "LINE") (100 . "AcDbEntity") (8 . "MASONRY") (62 . 7) (370 . 13) (100 . "AcDbLine") (10 16210.407239819
3408.7478846154 0.0) (11 16329.185520362 3408.7478846154 0.0))
((0 . "LINE") (100 . "AcDbEntity") (8 . "MASONRY") (62 . 7) (370 . 13) (100 . "AcDbLine") (10 16327.3019909502
3186.2008597285 0.0) (11 16200.9813122172 3186.2008597285 0.0))
((0 . "LINE") (100 . "AcDbEntity") (8 . "MASONRY") (62 . 7) (370 . 13) (100 . "AcDbLine") (10 16202.86760181
1864.6309276018 0.0) (11 16233.0316742081 1864.6309276018 0.0))
((0 . "LINE") (100 . "AcDbEntity") (8 . "MASONRY") (62 . 7) (370 . 13) (100 . "AcDbLine") (10 16206.6374208145
1541.0341289593 0.0) (11 16206.6374208145 1583.7104072398 0.0))
((0 . "LINE") (100 . "AcDbEntity") (8 . "MASONRY") (62 . 7) (370 . 13) (100 . "AcDbLine") (10 16414.0271493213
3254.1480429864 0.0) (11 16199.0950226244 3254.1480429864 0.0))
((0 . "LINE") (100 . "AcDbEntity") (8 . "MASONRY") (62 . 7) (370 . 13) (100 . "AcDbLine") (10 16259.4286877828
2969.4570135747 0.0) (11 16206.6346606335 2969.4570135747 0.0))
((0 . "LINE") (100 . "AcDbEntity") (8 . "MASONRY") (62 . 7) (370 . 13) (100 . "AcDbLine") (10 16349.9264253394
1987.1797171946 0.0) (11 16208.5209502262 1987.1797171946 0.0))
((0 . "LINE") (100 . "AcDbEntity") (8 . "MASONRY") (62 . 7) (370 . 13) (100 . "AcDbLine") (10 16208.5209502262
2030.6907466063 0.0) (11 16208.5209502262 1987.1797171946 0.0))
((0 . "LINE") (100 . "AcDbEntity") (8 . "MASONRY") (62 . 7) (370 . 13) (100 . "AcDbLine") (10 16208.5209502262
2030.6907466063 0.0) (11 16432.8790045249 2030.6907466063 0.0))
((0 . "LINE") (100 . "AcDbEntity") (8 . "MASONRY") (62 . 7) (370 . 13) (100 . "AcDbLine") (10 16432.8790045249
2030.6907466063 0.0) (11 16464.9321266968 2030.6907466063 0.0))
((0 . "LINE") (100 . "AcDbEntity") (8 . "MASONRY") (62 . 7) (370 . 13) (100 . "AcDbLine") (10 16210.407239819
1734.5390497738 0.0) (11 16210.407239819 1726.9994117647 0.0))
((0 . "LINE") (100 . "AcDbEntity") (8 . "MASONRY") (62 . 7) (370 . 13) (100 . "AcDbLine") (10 16206.6374208145
1541.0341289593 0.0) (11 16515.8371040724 1541.0341289593 0.0))
((0 . "LINE") (100 . "AcDbEntity") (8 . "MASONRY") (62 . 7) (370 . 13) (100 . "AcDbLine") (10 16214.1798190045
2401.9612443439 0.0) (11 16485.6730316742 2401.9612443439 0.0))
((0 . "LINE") (100 . "AcDbEntity") (8 . "MASONRY") (62 . 7) (370 . 13) (100 . "AcDbLine") (10 16217.9496380091
2168.1751923077 0.0) (11 16217.9496380091 2190.1975565611 0.0))
((0 . "LINE") (100 . "AcDbEntity") (8 . "MASONRY") (62 . 7) (370 . 13) (100 . "AcDbLine") (10 16214.1798190045
1670.4383257919 0.0) (11 16214.1798190045 1644.0413122172 0.0))
((0 . "LINE") (100 . "AcDbEntity") (8 . "MASONRY") (62 . 7) (370 . 13) (100 . "AcDbLine") (10 16481.9004524887
1738.2342986425 0.0) (11 16338.54239819 1738.2342986425 0.0))
((0 . "LINE") (100 . "AcDbEntity") (8 . "MASONRY") (62 . 7) (370 . 13) (100 . "AcDbLine") (10 16338.54239819
1738.2342986425 0.0) (11 16338.54239819 1670.4383257919 0.0))
((0 . "LINE") (100 . "AcDbEntity") (8 . "MASONRY") (62 . 7) (370 . 13) (100 . "AcDbLine") (10 16338.54239819
1670.4383257919 0.0) (11 16214.1798190045 1670.4383257919 0.0))
((0 . "LINE") (100 . "AcDbEntity") (8 . "MASONRY") (62 . 7) (370 . 13) (100 . "AcDbLine") (10 16278.2805429864
3099.5475113122 0.0) (11 16217.9468778281 3099.5475113122 0.0))
((0 . "LINE") (100 . "AcDbEntity") (8 . "MASONRY") (62 . 7) (370 . 13) (100 . "AcDbLine") (10 16217.9468778281
2098.4162895928 0.0) (11 16217.9468778281 2070.1357466063 0.0))
((0 . "LINE") (100 . "AcDbEntity") (8 . "MASONRY") (62 . 7) (370 . 13) (100 . "AcDbLine") (10 16217.9468778281
2098.4162895928 0.0) (11 16217.9468778281 2122.9263235294 0.0))
((0 . "LINE") (100 . "AcDbEntity") (8 . "MASONRY") (62 . 7) (370 . 13) (100 . "AcDbLine") (10 16704.3722171946
2190.1975565611 0.0) (11 16217.9496380091 2190.1975565611 0.0))
((0 . "LINE") (100 . "AcDbEntity") (8 . "MASONRY") (62 . 7) (370 . 13) (100 . "AcDbLine") (10 16246.753540724
515.588959276 0.0) (11 16246.753540724 565.6108597285 0.0))
((0 . "LINE") (100 . "AcDbEntity") (8 . "MASONRY") (62 . 7) (370 . 13) (100 . "AcDbLine") (10 16339.2922285068
577.8358371041 0.0) (11 16214.8536877828 577.8358371041 0.0))
((0 . "LINE") (100 . "AcDbEntity") (8 . "MASONRY") (62 . 7) (370 . 13) (100 . "AcDbLine") (10 16214.8536877828
577.8358371041 0.0) (11 16214.8536877828 565.6108597285 0.0))
((0 . "LINE") (100 . "AcDbEntity") (8 . "MASONRY") (62 . 7) (370 . 13) (100 . "AcDbLine") (10 16214.8536877828
565.6108597285 0.0) (11 16246.753540724 565.6108597285 0.0))
((0 . "LINE") (100 . "AcDbEntity") (8 . "MASONRY") (62 . 7) (370 . 13) (100 . "AcDbLine") (10 16246.753540724
565.6108597285 0.0) (11 16304.8846945701 565.6108597285 0.0))
((0 . "LINE") (100 . "AcDbEntity") (8 . "MASONRY") (62 . 7) (370 . 13) (100 . "AcDbLine") (10 16255.6561085973
1330.469739819 0.0) (11 16238.7651131222 1330.469739819 0.0))
((0 . "LINE") (100 . "AcDbEntity") (8 . "MASONRY") (62 . 7) (370 . 13) (100 . "AcDbLine") (10 16238.7651131222
1330.469739819 0.0) (11 16238.7651131222 1312.2171945701 0.0))
((0 . "LINE") (100 . "AcDbEntity") (8 . "MASONRY") (62 . 7) (370 . 13) (100 . "AcDbLine") (10 16576.1707692308
1180.2404072398 0.0) (11 16242.5349321267 1180.2404072398 0.0))
((0 . "LINE") (100 . "AcDbEntity") (8 . "MASONRY") (62 . 7) (370 . 13) (100 . "AcDbLine") (10 16338.6114479638
1251.8862895928 0.0) (11 16338.6114479638 1231.0721945701 0.0))
((0 . "LINE") (100 . "AcDbEntity") (8 . "MASONRY") (62 . 7) (370 . 13) (100 . "AcDbLine") (10 16338.6114479638
1231.0721945701 0.0) (11 16242.5349321267 1231.0721945701 0.0))
((0 . "LINE") (100 . "AcDbEntity") (8 . "MASONRY") (62 . 7) (370 . 13) (100 . "AcDbLine") (10 16242.5349321267
1231.0721945701 0.0) (11 16242.5349321267 1180.2404072398 0.0))
((0 . "LINE") (100 . "AcDbEntity") (8 . "MASONRY") (62 . 7) (370 . 13) (100 . "AcDbLine") (10 16278.2805429864
1419.6832579186 0.0) (11 16251.8835294118 1419.6832579186 0.0))
((0 . "LINE") (100 . "AcDbEntity") (8 . "MASONRY") (62 . 7) (370 . 13) (100 . "AcDbLine") (10 16345.5517760181
1862.822658371 0.0) (11 16319.7568325792 1862.822658371 0.0))
((0 . "LINE") (100 . "AcDbEntity") (8 . "MASONRY") (62 . 7) (370 . 13) (100 . "AcDbLine") (10 16319.7568325792
1862.822658371 0.0) (11 16263.1957466063 1862.822658371 0.0))
((0 . "LINE") (100 . "AcDbEntity") (8 . "MASONRY") (62 . 7) (370 . 13) (100 . "AcDbLine") (10 16876.0190950226
1331.0718099548 0.0) (11 16278.2805429864 1331.0718099548 0.0))
((0 . "LINE") (100 . "AcDbEntity") (8 . "MASONRY") (62 . 7) (370 . 13) (100 . "AcDbLine") (10 16285.8201809955
3045.0563687783 0.0) (11 16325.2348076923 3045.0563687783 0.0))
((0 . "LINE") (100 . "AcDbEntity") (8 . "MASONRY") (62 . 7) (370 . 13) (100 . "AcDbLine") (10 16325.2348076923
3045.0563687783 0.0) (11 16325.2348076923 3099.5475113122 0.0))
((0 . "LINE") (100 . "AcDbEntity") (8 . "MASONRY") (62 . 7) (370 . 13) (100 . "AcDbLine") (10 16289.592760181
957.7686425339 0.0) (11 16289.592760181 939.0686877828 0.0))
((0 . "LINE") (100 . "AcDbEntity") (8 . "MASONRY") (62 . 7) (370 . 13) (100 . "AcDbLine") (10 16289.592760181
939.0686877828 0.0) (11 16551.6600452489 939.0686877828 0.0))
((0 . "LINE") (100 . "AcDbEntity") (8 . "MASONRY") (62 . 7) (370 . 13) (100 . "AcDbLine") (10 16289.592760181
957.7686425339 0.0) (11 16289.592760181 987.9327149321 0.0))
((0 . "LINE") (100 . "AcDbEntity") (8 . "MASONRY") (62 . 7) (370 . 13) (100 . "AcDbLine") (10 16293.3653393665
886.1241402715 0.0) (11 16414.0271493213 886.1241402715 0.0))
((0 . "LINE") (100 . "AcDbEntity") (8 . "MASONRY") (62 . 7) (370 . 13) (100 . "AcDbLine") (10 16387.6301357466
1421.5695475113 0.0) (11 16297.13239819 1421.5695475113 0.0))
((0 . "LINE") (100 . "AcDbEntity") (8 . "MASONRY") (62 . 7) (370 . 13) (100 . "AcDbLine") (10 16304.6775565611
3099.5475113122 0.0) (11 16325.2348076923 3099.5475113122 0.0))
((0 . "LINE") (100 . "AcDbEntity") (8 . "MASONRY") (62 . 7) (370 . 13) (100 . "AcDbLine") (10 16312.2171945701
2507.5417081448 0.0) (11 16327.3019909502 2507.5417081448 0.0))
((0 . "LINE") (100 . "AcDbEntity") (8 . "MASONRY") (62 . 7) (370 . 13) (100 . "AcDbLine") (10 16329.185520362
3374.8112330317 0.0) (11 16329.185520362 3408.7478846154 0.0))
((0 . "LINE") (100 . "AcDbEntity") (8 . "MASONRY") (62 . 7) (370 . 13) (100 . "AcDbLine") (10 16329.185520362
3408.7478846154 0.0) (11 16417.7997285068 3408.7478846154 0.0))
((0 . "LINE") (100 . "AcDbEntity") (8 . "MASONRY") (62 . 7) (370 . 13) (100 . "AcDbLine") (10 16327.3019909502
3186.2008597285 0.0) (11 16327.3019909502 3212.6696832579 0.0))
((0 . "LINE") (100 . "AcDbEntity") (8 . "MASONRY") (62 . 7) (370 . 13) (100 . "AcDbLine") (10 16327.3019909502
3186.2008597285 0.0) (11 16349.9264253394 3186.2008597285 0.0))
((0 . "LINE") (100 . "AcDbEntity") (8 . "MASONRY") (62 . 7) (370 . 13) (100 . "AcDbLine") (10 16349.9264253394
3186.2008597285 0.0) (11 16395.1752941176 3186.2008597285 0.0))
((0 . "LINE") (100 . "AcDbEntity") (8 . "MASONRY") (62 . 7) (370 . 13) (100 . "AcDbLine") (10 16417.7997285068
3099.5475113122 0.0) (11 16325.2348076923 3099.5475113122 0.0))
((0 . "LINE") (100 . "AcDbEntity") (8 . "MASONRY") (62 . 7) (370 . 13) (100 . "AcDbLine") (10 16327.3019909502
2714.9321266968 0.0) (11 16327.3019909502 2722.4738348416 0.0))
((0 . "LINE") (100 . "AcDbEntity") (8 . "MASONRY") (62 . 7) (370 . 13) (100 . "AcDbLine") (10 16327.3019909502
2507.5417081448 0.0) (11 16421.5667873303 2507.5417081448 0.0))
((0 . "LINE") (100 . "AcDbEntity") (8 . "MASONRY") (62 . 7) (370 . 13) (100 . "AcDbLine") (10 16327.3019909502
2507.5417081448 0.0) (11 16327.3019909502 2590.4977375566 0.0))
((0 . "LINE") (100 . "AcDbEntity") (8 . "MASONRY") (62 . 7) (370 . 13) (100 . "AcDbLine") (10 16327.3019909502
2590.4977375566 0.0) (11 16327.3019909502 2622.471459276 0.0))
((0 . "LINE") (100 . "AcDbEntity") (8 . "MASONRY") (62 . 7) (370 . 13) (100 . "AcDbLine") (10 16327.3019909502
2622.471459276 0.0) (11 16410.2545701357 2622.471459276 0.0))
((0 . "LINE") (100 . "AcDbEntity") (8 . "MASONRY") (62 . 7) (370 . 13) (100 . "AcDbLine") (10 16345.5517760181
1862.822658371 0.0) (11 16345.5517760181 1894.7190497738 0.0))
((0 . "LINE") (100 . "AcDbEntity") (8 . "MASONRY") (62 . 7) (370 . 13) (100 . "AcDbLine") (10 16345.5517760181
1894.7190497738 0.0) (11 16327.3019909502 1894.7190497738 0.0))
((0 . "LINE") (100 . "AcDbEntity") (8 . "MASONRY") (62 . 7) (370 . 13) (100 . "AcDbLine") (10 16327.3019909502
1817.4971493213 0.0) (11 16338.6142081448 1817.4971493213 0.0))
((0 . "LINE") (100 . "AcDbEntity") (8 . "MASONRY") (62 . 7) (370 . 13) (100 . "AcDbLine") (10 16327.3019909502
723.9819004525 0.0) (11 16346.1538461538 723.9819004525 0.0))
((0 . "LINE") (100 . "AcDbEntity") (8 . "MASONRY") (62 . 7) (370 . 13) (100 . "AcDbLine") (10 16338.6142081448
3337.1040723982 0.0) (11 16349.9264253394 3337.1040723982 0.0))
((0 . "LINE") (100 . "AcDbEntity") (8 . "MASONRY") (62 . 7) (370 . 13) (100 . "AcDbLine") (10 16349.9264253394
3337.1040723982 0.0) (11 16417.7997285068 3337.1040723982 0.0))
((0 . "LINE") (100 . "AcDbEntity") (8 . "MASONRY") (62 . 7) (370 . 13) (100 . "AcDbLine") (10 16414.0271493213
2828.0542986425 0.0) (11 16342.3812669683 2828.0542986425 0.0))
((0 . "LINE") (100 . "AcDbEntity") (8 . "MASONRY") (62 . 7) (370 . 13) (100 . "AcDbLine") (10 16342.3812669683
2760.1809954751 0.0) (11 16342.3812669683 2828.0542986425 0.0))
((0 . "LINE") (100 . "AcDbEntity") (8 . "MASONRY") (62 . 7) (370 . 13) (100 . "AcDbLine") (10 16342.3812669683
2828.0542986425 0.0) (11 16342.3812669683 2895.92760181 0.0))
((0 . "LINE") (100 . "AcDbEntity") (8 . "MASONRY") (62 . 7) (370 . 13) (100 . "AcDbLine") (10 16342.3812669683
2760.1809954751 0.0) (11 16417.7997285068 2760.1809954751 0.0))
((0 . "LINE") (100 . "AcDbEntity") (8 . "MASONRY") (62 . 7) (370 . 13) (100 . "AcDbLine") (10 16361.2386425339
3142.910780543 0.0) (11 16346.1538461538 3142.910780543 0.0))
((0 . "LINE") (100 . "AcDbEntity") (8 . "MASONRY") (62 . 7) (370 . 13) (100 . "AcDbLine") (10 16414.0271493213
2895.92760181 0.0) (11 16342.3812669683 2895.92760181 0.0))
((0 . "LINE") (100 . "AcDbEntity") (8 . "MASONRY") (62 . 7) (370 . 13) (100 . "AcDbLine") (10 16345.5517760181
1862.822658371 0.0) (11 16376.317918552 1862.822658371 0.0))
((0 . "LINE") (100 . "AcDbEntity") (8 . "MASONRY") (62 . 7) (370 . 13) (100 . "AcDbLine") (10 16376.317918552
1862.822658371 0.0) (11 16538.4615384615 1862.822658371 0.0))
((0 . "LINE") (100 . "AcDbEntity") (8 . "MASONRY") (62 . 7) (370 . 13) (100 . "AcDbLine") (10 16349.9264253394
1078.4318325792 0.0) (11 16581.8241176471 1078.4318325792 0.0))
((0 . "LINE") (100 . "AcDbEntity") (8 . "MASONRY") (62 . 7) (370 . 13) (100 . "AcDbLine") (10 16349.9264253394
617.9547171946 0.0) (11 16357.9687104072 617.9547171946 0.0))
((0 . "LINE") (100 . "AcDbEntity") (8 . "MASONRY") (62 . 7) (370 . 13) (100 . "AcDbLine") (10 16595.0226244344
1953.2423755656 0.0) (11 16357.4660633484 1953.2423755656 0.0))
((0 . "LINE") (100 . "AcDbEntity") (8 . "MASONRY") (62 . 7) (370 . 13) (100 . "AcDbLine") (10 16365.0057013575
2598.0394457014 0.0) (11 16417.7997285068 2598.0394457014 0.0))
((0 . "LINE") (100 . "AcDbEntity") (8 . "MASONRY") (62 . 7) (370 . 13) (100 . "AcDbLine") (10 16417.7997285068
3029.7892986425 0.0) (11 16368.778280543 3029.7892986425 0.0))
((0 . "LINE") (100 . "AcDbEntity") (8 . "MASONRY") (62 . 7) (370 . 13) (100 . "AcDbLine") (10 16383.8630769231
1685.520361991 0.0) (11 16653.47 1685.520361991 0.0))
((0 . "LINE") (100 . "AcDbEntity") (8 . "MASONRY") (62 . 7) (370 . 13) (100 . "AcDbLine") (10 16387.6301357466
812.7452488688 0.0) (11 16387.6301357466 825.7918552036 0.0))
((0 . "LINE") (100 . "AcDbEntity") (8 . "MASONRY") (62 . 7) (370 . 13) (100 . "AcDbLine") (10 16387.6301357466
1421.5695475113 0.0) (11 16387.6301357466 1455.506199095 0.0))
((0 . "LINE") (100 . "AcDbEntity") (8 . "MASONRY") (62 . 7) (370 . 13) (100 . "AcDbLine") (10 16387.6301357466
1421.5695475113 0.0) (11 16387.6301357466 1402.7922624434 0.0))
((0 . "LINE") (100 . "AcDbEntity") (8 . "MASONRY") (62 . 7) (370 . 13) (100 . "AcDbLine") (10 16387.6301357466
1365.0084615385 0.0) (11 16387.6301357466 1402.7922624434 0.0))
((0 . "LINE") (100 . "AcDbEntity") (8 . "MASONRY") (62 . 7) (370 . 13) (100 . "AcDbLine") (10 16416.8510633484
812.7452488688 0.0) (11 16387.6301357466 812.7452488688 0.0))
((0 . "LINE") (100 . "AcDbEntity") (8 . "MASONRY") (62 . 7) (370 . 13) (100 . "AcDbLine") (10 16387.6301357466
812.7452488688 0.0) (11 16387.6301357466 755.6545927602 0.0))
((0 . "LINE") (100 . "AcDbEntity") (8 . "MASONRY") (62 . 7) (370 . 13) (100 . "AcDbLine") (10 16417.7997285068
2554.6761764706 0.0) (11 16391.4027149321 2554.6761764706 0.0))
((0 . "LINE") (100 . "AcDbEntity") (8 . "MASONRY") (62 . 7) (370 . 13) (100 . "AcDbLine") (10 16387.6301357466
1402.7922624434 0.0) (11 16593.1363348416 1402.7922624434 0.0))
((0 . "LINE") (100 . "AcDbEntity") (8 . "MASONRY") (62 . 7) (370 . 13) (100 . "AcDbLine") (10 16593.1363348416
1402.7922624434 0.0) (11 16593.1363348416 1425.3393665158 0.0))
((0 . "LINE") (100 . "AcDbEntity") (8 . "MASONRY") (62 . 7) (370 . 13) (100 . "AcDbLine") (10 16415.913438914
3148.5668891403 0.0) (11 16415.913438914 3137.2546719457 0.0))
((0 . "LINE") (100 . "AcDbEntity") (8 . "MASONRY") (62 . 7) (370 . 13) (100 . "AcDbLine") (10 16521.4932126697
2263.6524095023 0.0) (11 16508.2974660633 2263.6524095023 0.0))
((0 . "LINE") (100 . "AcDbEntity") (8 . "MASONRY") (62 . 7) (370 . 13) (100 . "AcDbLine") (10 16508.2974660633
2263.6524095023 0.0) (11 16474.3608144796 2263.6524095023 0.0))
((0 . "LINE") (100 . "AcDbEntity") (8 . "MASONRY") (62 . 7) (370 . 13) (100 . "AcDbLine") (10 16474.3608144796
2263.6524095023 0.0) (11 16451.740520362 2263.6524095023 0.0))
((0 . "LINE") (100 . "AcDbEntity") (8 . "MASONRY") (62 . 7) (370 . 13) (100 . "AcDbLine") (10 16451.740520362
2263.6524095023 0.0) (11 16440.4241628959 2263.6524095023 0.0))
((0 . "LINE") (100 . "AcDbEntity") (8 . "MASONRY") (62 . 7) (370 . 13) (100 . "AcDbLine") (10 16444.1912217195
2100.3018891403 0.0) (11 16464.9321266968 2100.3018891403 0.0))
((0 . "LINE") (100 . "AcDbEntity") (8 . "MASONRY") (62 . 7) (370 . 13) (100 . "AcDbLine") (10 16450.4521606335
995.4751131222 0.0) (11 16444.1912217195 995.4751131222 0.0))
((0 . "LINE") (100 . "AcDbEntity") (8 . "MASONRY") (62 . 7) (370 . 13) (100 . "AcDbLine") (10 16450.4521606335
995.4751131222 0.0) (11 16450.4521606335 1027.5234049774 0.0))
((0 . "LINE") (100 . "AcDbEntity") (8 . "MASONRY") (62 . 7) (370 . 13) (100 . "AcDbLine") (10 16450.4521606335
1027.5234049774 0.0) (11 16470.5882352941 1027.5234049774 0.0))
((0 . "LINE") (100 . "AcDbEntity") (8 . "MASONRY") (62 . 7) (370 . 13) (100 . "AcDbLine") (10 16450.4521606335
995.4751131222 0.0) (11 16745.8540271493 995.4751131222 0.0))
((0 . "LINE") (100 . "AcDbEntity") (8 . "MASONRY") (62 . 7) (370 . 13) (100 . "AcDbLine") (10 16542.2341176471
888.0090497738 0.0) (11 16451.7363800905 888.0090497738 0.0))
((0 . "LINE") (100 . "AcDbEntity") (8 . "MASONRY") (62 . 7) (370 . 13) (100 . "AcDbLine") (10 16666.6685067873
2317.1196153846 0.0) (11 16459.2760180996 2317.1196153846 0.0))
((0 . "LINE") (100 . "AcDbEntity") (8 . "MASONRY") (62 . 7) (370 . 13) (100 . "AcDbLine") (10 16464.9321266968
2100.3018891403 0.0) (11 16464.9321266968 2030.6907466063 0.0))
((0 . "LINE") (100 . "AcDbEntity") (8 . "MASONRY") (62 . 7) (370 . 13) (100 . "AcDbLine") (10 16523.3767420815
2100.3018891403 0.0) (11 16464.9321266968 2100.3018891403 0.0))
((0 . "LINE") (100 . "AcDbEntity") (8 . "MASONRY") (62 . 7) (370 . 13) (100 . "AcDbLine") (10 16478.1278733032
2030.6907466063 0.0) (11 16464.9321266968 2030.6907466063 0.0))
((0 . "LINE") (100 . "AcDbEntity") (8 . "MASONRY") (62 . 7) (370 . 13) (100 . "AcDbLine") (10 16481.9004524887
825.7918552036 0.0) (11 16606.334841629 825.7918552036 0.0))
((0 . "LINE") (100 . "AcDbEntity") (8 . "MASONRY") (62 . 7) (370 . 13) (100 . "AcDbLine") (10 16500.7523076923
1598.7924434389 0.0) (11 16515.8371040724 1598.7924434389 0.0))
((0 . "LINE") (100 . "AcDbEntity") (8 . "MASONRY") (62 . 7) (370 . 13) (100 . "AcDbLine") (10 16504.5248868778
3535.0678733032 0.0) (11 16512.0645248869 3535.0678733032 0.0))
((0 . "LINE") (100 . "AcDbEntity") (8 . "MASONRY") (62 . 7) (370 . 13) (100 . "AcDbLine") (10 16517.7233936652
1463.0458371041 0.0) (11 16508.2974660633 1463.0458371041 0.0))
((0 . "LINE") (100 . "AcDbEntity") (8 . "MASONRY") (62 . 7) (370 . 13) (100 . "AcDbLine") (10 16508.2974660633
1274.5107239819 0.0) (11 16508.2974660633 1255.6561085973 0.0))
((0 . "LINE") (100 . "AcDbEntity") (8 . "MASONRY") (62 . 7) (370 . 13) (100 . "AcDbLine") (10 16508.2974660633
1285.8229411765 0.0) (11 16508.2974660633 1274.5107239819 0.0))
((0 . "LINE") (100 . "AcDbEntity") (8 . "MASONRY") (62 . 7) (370 . 13) (100 . "AcDbLine") (10 16512.0645248869
2409.5768325792 0.0) (11 16542.2341176471 2409.5768325792 0.0))
((0 . "LINE") (100 . "AcDbEntity") (8 . "MASONRY") (62 . 7) (370 . 13) (100 . "AcDbLine") (10 16542.2341176471
2409.5768325792 0.0) (11 16542.2341176471 2424.5849886878 0.0))
((0 . "LINE") (100 . "AcDbEntity") (8 . "MASONRY") (62 . 7) (370 . 13) (100 . "AcDbLine") (10 16583.7104072398
2036.1990950226 0.0) (11 16512.0645248869 2036.1990950226 0.0))
((0 . "LINE") (100 . "AcDbEntity") (8 . "MASONRY") (62 . 7) (370 . 13) (100 . "AcDbLine") (10 16519.6096832579
1233.0316742081 0.0) (11 16512.0645248869 1233.0316742081 0.0))
((0 . "LINE") (100 . "AcDbEntity") (8 . "MASONRY") (62 . 7) (370 . 13) (100 . "AcDbLine") (10 16538.4615384615
1598.7924434389 0.0) (11 16515.8371040724 1598.7924434389 0.0))
((0 . "LINE") (100 . "AcDbEntity") (8 . "MASONRY") (62 . 7) (370 . 13) (100 . "AcDbLine") (10 16515.8371040724
1598.7924434389 0.0) (11 16515.8371040724 1541.0341289593 0.0))
((0 . "LINE") (100 . "AcDbEntity") (8 . "MASONRY") (62 . 7) (370 . 13) (100 . "AcDbLine") (10 16866.5158371041
1541.0341289593 0.0) (11 16515.8371040724 1541.0341289593 0.0))
((0 . "LINE") (100 . "AcDbEntity") (8 . "MASONRY") (62 . 7) (370 . 13) (100 . "AcDbLine") (10 16681.7477828054
1463.0458371041 0.0) (11 16517.7233936652 1463.0458371041 0.0))
((0 . "LINE") (100 . "AcDbEntity") (8 . "MASONRY") (62 . 7) (370 . 13) (100 . "AcDbLine") (10 16517.7233936652
1463.0458371041 0.0) (11 16517.7233936652 1500.7550678733 0.0))
((0 . "LINE") (100 . "AcDbEntity") (8 . "MASONRY") (62 . 7) (370 . 13) (100 . "AcDbLine") (10 16521.4932126697
2263.6524095023 0.0) (11 16521.4932126697 2232.2772963801 0.0))
((0 . "LINE") (100 . "AcDbEntity") (8 . "MASONRY") (62 . 7) (370 . 13) (100 . "AcDbLine") (10 16521.4932126697
2263.6524095023 0.0) (11 16704.3722171946 2263.6524095023 0.0))
((0 . "LINE") (100 . "AcDbEntity") (8 . "MASONRY") (62 . 7) (370 . 13) (100 . "AcDbLine") (10 16523.3767420815
1742.0814479638 0.0) (11 16549.7737556561 1742.0814479638 0.0))
((0 . "LINE") (100 . "AcDbEntity") (8 . "MASONRY") (62 . 7) (370 . 13) (100 . "AcDbLine") (10 16538.4615384615
1862.822658371 0.0) (11 16538.4615384615 1810.556821267 0.0))
((0 . "LINE") (100 . "AcDbEntity") (8 . "MASONRY") (62 . 7) (370 . 13) (100 . "AcDbLine") (10 16538.4615384615
1862.822658371 0.0) (11 16634.6153846154 1862.822658371 0.0))
((0 . "LINE") (100 . "AcDbEntity") (8 . "MASONRY") (62 . 7) (370 . 13) (100 . "AcDbLine") (10 16538.4615384615
1779.787918552 0.0) (11 16538.4615384615 1810.556821267 0.0))
((0 . "LINE") (100 . "AcDbEntity") (8 . "MASONRY") (62 . 7) (370 . 13) (100 . "AcDbLine") (10 16542.2341176471
2458.5216402715 0.0) (11 16542.2341176471 2424.5849886878 0.0))
((0 . "LINE") (100 . "AcDbEntity") (8 . "MASONRY") (62 . 7) (370 . 13) (100 . "AcDbLine") (10 16713.8009049774
1862.822658371 0.0) (11 16713.8009049774 1810.556821267 0.0))
((0 . "LINE") (100 . "AcDbEntity") (8 . "MASONRY") (62 . 7) (370 . 13) (100 . "AcDbLine") (10 16713.8009049774
1810.556821267 0.0) (11 16538.4615384615 1810.556821267 0.0))
((0 . "LINE") (100 . "AcDbEntity") (8 . "MASONRY") (62 . 7) (370 . 13) (100 . "AcDbLine") (10 16542.2341176471
2424.5849886878 0.0) (11 16674.2081447964 2424.5849886878 0.0))
((0 . "LINE") (100 . "AcDbEntity") (8 . "MASONRY") (62 . 7) (370 . 13) (100 . "AcDbLine") (10 16551.6600452489
939.0686877828 0.0) (11 16551.6600452489 920.0594117647 0.0))
((0 . "LINE") (100 . "AcDbEntity") (8 . "MASONRY") (62 . 7) (370 . 13) (100 . "AcDbLine") (10 16551.6600452489
939.0686877828 0.0) (11 16602.5622624434 939.0686877828 0.0))
((0 . "LINE") (100 . "AcDbEntity") (8 . "MASONRY") (62 . 7) (370 . 13) (100 . "AcDbLine") (10 16653.47 1600.6787330317
0.0) (11 16557.3133936652 1600.6787330317 0.0))
((0 . "LINE") (100 . "AcDbEntity") (8 . "MASONRY") (62 . 7) (370 . 13) (100 . "AcDbLine") (10 16568.6256108597
1285.8229411765 0.0) (11 16561.0859728507 1285.8229411765 0.0))
((0 . "LINE") (100 . "AcDbEntity") (8 . "MASONRY") (62 . 7) (370 . 13) (100 . "AcDbLine") (10 16595.0226244344
2107.8429072398 0.0) (11 16564.8585520362 2107.8429072398 0.0))
((0 . "LINE") (100 . "AcDbEntity") (8 . "MASONRY") (62 . 7) (370 . 13) (100 . "AcDbLine") (10 16633.074321267
686.9817533937 0.0) (11 16633.074321267 806.6907466063 0.0))
((0 . "LINE") (100 . "AcDbEntity") (8 . "MASONRY") (62 . 7) (370 . 13) (100 . "AcDbLine") (10 16705.0460859729
851.7663235294 0.0) (11 16724.3315384615 851.7663235294 0.0))
((0 . "LINE") (100 . "AcDbEntity") (8 . "MASONRY") (62 . 7) (370 . 13) (100 . "AcDbLine") (10 16724.3315384615
851.7663235294 0.0) (11 16724.3315384615 815.012658371 0.0))
((0 . "LINE") (100 . "AcDbEntity") (8 . "MASONRY") (62 . 7) (370 . 13) (100 . "AcDbLine") (10 16576.1707692308
1180.2404072398 0.0) (11 16576.1707692308 1168.9281900452 0.0))
((0 . "LINE") (100 . "AcDbEntity") (8 . "MASONRY") (62 . 7) (370 . 13) (100 . "AcDbLine") (10 16576.1707692308
1180.2404072398 0.0) (11 16693.06 1180.2404072398 0.0))
((0 . "LINE") (100 . "AcDbEntity") (8 . "MASONRY") (62 . 7) (370 . 13) (100 . "AcDbLine") (10 16636.4989140272
3508.6729298643 0.0) (11 16579.9378280543 3508.6729298643 0.0))
((0 . "LINE") (100 . "AcDbEntity") (8 . "MASONRY") (62 . 7) (370 . 13) (100 . "AcDbLine") (10 17179.4853393665
1743.9663574661 0.0) (11 16579.9378280543 1743.9663574661 0.0))
((0 . "LINE") (100 . "AcDbEntity") (8 . "MASONRY") (62 . 7) (370 . 13) (100 . "AcDbLine") (10 16579.9378280543
1121.7944117647 0.0) (11 16659.1233484163 1121.7944117647 0.0))
((0 . "LINE") (100 . "AcDbEntity") (8 . "MASONRY") (62 . 7) (370 . 13) (100 . "AcDbLine") (10 16581.8241176471
1078.4318325792 0.0) (11 16581.8241176471 1093.5152488688 0.0))
((0 . "LINE") (100 . "AcDbEntity") (8 . "MASONRY") (62 . 7) (370 . 13) (100 . "AcDbLine") (10 16581.8241176471
1078.4318325792 0.0) (11 17075.7918552036 1078.4318325792 0.0))
((0 . "LINE") (100 . "AcDbEntity") (8 . "MASONRY") (62 . 7) (370 . 13) (100 . "AcDbLine") (10 16602.5622624434
920.0594117647 0.0) (11 16602.5622624434 939.0686877828 0.0))
((0 . "LINE") (100 . "AcDbEntity") (8 . "MASONRY") (62 . 7) (370 . 13) (100 . "AcDbLine") (10 16889.1402714932
939.0686877828 0.0) (11 16602.5622624434 939.0686877828 0.0))
((0 . "LINE") (100 . "AcDbEntity") (8 . "MASONRY") (62 . 7) (370 . 13) (100 . "AcDbLine") (10 16602.5622624434
886.1241402715 0.0) (11 16610.1074208145 886.1241402715 0.0))
((0 . "LINE") (100 . "AcDbEntity") (8 . "MASONRY") (62 . 7) (370 . 13) (100 . "AcDbLine") (10 16613.874479638
2036.1990950226 0.0) (11 16644.0440723982 2036.1990950226 0.0))
((0 . "LINE") (100 . "AcDbEntity") (8 . "MASONRY") (62 . 7) (370 . 13) (100 . "AcDbLine") (10 16651.5837104072
2105.9573076923 0.0) (11 16621.4196380091 2105.9573076923 0.0))
((0 . "LINE") (100 . "AcDbEntity") (8 . "MASONRY") (62 . 7) (370 . 13) (100 . "AcDbLine") (10 16628.9592760181
1285.8229411765 0.0) (11 16659.1233484163 1285.8229411765 0.0))
((0 . "LINE") (100 . "AcDbEntity") (8 . "MASONRY") (62 . 7) (370 . 13) (100 . "AcDbLine") (10 16870.2884162896
1955.1286651584 0.0) (11 16632.7318552036 1955.1286651584 0.0))
((0 . "LINE") (100 . "AcDbEntity") (8 . "MASONRY") (62 . 7) (370 . 13) (100 . "AcDbLine") (10 16713.8009049774
1862.822658371 0.0) (11 16634.6153846154 1862.822658371 0.0))
((0 . "LINE") (100 . "AcDbEntity") (8 . "MASONRY") (62 . 7) (370 . 13) (100 . "AcDbLine") (10 16634.6153846154
1877.8280542986 0.0) (11 16634.6153846154 1862.822658371 0.0))
((0 . "LINE") (100 . "AcDbEntity") (8 . "MASONRY") (62 . 7) (370 . 13) (100 . "AcDbLine") (10 16632.7318552036
1434.7666742081 0.0) (11 17009.802081448 1434.7666742081 0.0))
((0 . "LINE") (100 . "AcDbEntity") (8 . "MASONRY") (62 . 7) (370 . 13) (100 . "AcDbLine") (10 16776.0180995475
3256.1848529412 0.0) (11 16749.6210859729 3256.1848529412 0.0))
((0 . "LINE") (100 . "AcDbEntity") (8 . "MASONRY") (62 . 7) (370 . 13) (100 . "AcDbLine") (10 16749.6210859729
3256.1848529412 0.0) (11 16651.5837104072 3256.1848529412 0.0))
((0 . "LINE") (100 . "AcDbEntity") (8 . "MASONRY") (62 . 7) (370 . 13) (100 . "AcDbLine") (10 16892.9128506787
2509.4273076923 0.0) (11 16651.5837104072 2509.4273076923 0.0))
((0 . "LINE") (100 . "AcDbEntity") (8 . "MASONRY") (62 . 7) (370 . 13) (100 . "AcDbLine") (10 16653.47 1685.520361991
0.0) (11 16653.47 1696.8325791855 0.0))
((0 . "LINE") (100 . "AcDbEntity") (8 . "MASONRY") (62 . 7) (370 . 13) (100 . "AcDbLine") (10 16653.47 1640.2714932127
0.0) (11 16653.47 1600.6787330317 0.0))
((0 . "LINE") (100 . "AcDbEntity") (8 . "MASONRY") (62 . 7) (370 . 13) (100 . "AcDbLine") (10 16892.9128506787
3050.5281334842 0.0) (11 16655.3562895928 3050.5281334842 0.0))
((0 . "LINE") (100 . "AcDbEntity") (8 . "MASONRY") (62 . 7) (370 . 13) (100 . "AcDbLine") (10 16674.2081447964
2779.0349208145 0.0) (11 16655.3562895928 2779.0349208145 0.0))
((0 . "LINE") (100 . "AcDbEntity") (8 . "MASONRY") (62 . 7) (370 . 13) (100 . "AcDbLine") (10 16670.4355656109
1685.520361991 0.0) (11 16653.47 1685.520361991 0.0))
((0 . "LINE") (100 . "AcDbEntity") (8 . "MASONRY") (62 . 7) (370 . 13) (100 . "AcDbLine") (10 16804.2986425339
1600.6787330317 0.0) (11 16653.47 1600.6787330317 0.0))
((0 . "LINE") (100 . "AcDbEntity") (8 . "MASONRY") (62 . 7) (370 . 13) (100 . "AcDbLine") (10 16659.1233484163
3514.3290384615 0.0) (11 16813.7273303167 3514.3290384615 0.0))
((0 . "LINE") (100 . "AcDbEntity") (8 . "MASONRY") (62 . 7) (370 . 13) (100 . "AcDbLine") (10 16659.1233484163
3340.874581448 0.0) (11 16687.4066515837 3340.874581448 0.0))
((0 . "LINE") (100 . "AcDbEntity") (8 . "MASONRY") (62 . 7) (370 . 13) (100 . "AcDbLine") (10 16691.1764705882
3107.089219457 0.0) (11 16659.1233484163 3107.089219457 0.0))
((0 . "LINE") (100 . "AcDbEntity") (8 . "MASONRY") (62 . 7) (370 . 13) (100 . "AcDbLine") (10 16659.1233484163
2895.92760181 0.0) (11 16870.2884162896 2895.92760181 0.0))
((0 . "LINE") (100 . "AcDbEntity") (8 . "MASONRY") (62 . 7) (370 . 13) (100 . "AcDbLine") (10 17130.4694117647
3182.799739819 0.0) (11 16806.1821719457 3182.799739819 0.0))
((0 . "LINE") (100 . "AcDbEntity") (8 . "MASONRY") (62 . 7) (370 . 13) (100 . "AcDbLine") (10 16806.1821719457
3182.799739819 0.0) (11 16715.6844343891 3182.799739819 0.0))
((0 . "LINE") (100 . "AcDbEntity") (8 . "MASONRY") (62 . 7) (370 . 13) (100 . "AcDbLine") (10 16715.6844343891
3182.799739819 0.0) (11 16666.6657466063 3182.799739819 0.0))
((0 . "LINE") (100 . "AcDbEntity") (8 . "MASONRY") (62 . 7) (370 . 13) (100 . "AcDbLine") (10 16666.6657466063
3182.799739819 0.0) (11 16666.6657466063 3159.8791063348 0.0))
((0 . "LINE") (100 . "AcDbEntity") (8 . "MASONRY") (62 . 7) (370 . 13) (100 . "AcDbLine") (10 16664.9672511312
2609.3516628959 0.0) (11 16664.9672511312 2633.8616968326 0.0))
((0 . "LINE") (100 . "AcDbEntity") (8 . "MASONRY") (62 . 7) (370 . 13) (100 . "AcDbLine") (10 16664.9672511312
2633.8616968326 0.0) (11 16870.2884162896 2633.8616968326 0.0))
((0 . "LINE") (100 . "AcDbEntity") (8 . "MASONRY") (62 . 7) (370 . 13) (100 . "AcDbLine") (10 16666.6685067873
2317.1196153846 0.0) (11 16666.6685067873 2352.9411764706 0.0))
((0 . "LINE") (100 . "AcDbEntity") (8 . "MASONRY") (62 . 7) (370 . 13) (100 . "AcDbLine") (10 16666.6685067873
2317.1196153846 0.0) (11 16704.3722171946 2317.1196153846 0.0))
((0 . "LINE") (100 . "AcDbEntity") (8 . "MASONRY") (62 . 7) (370 . 13) (100 . "AcDbLine") (10 16674.2081447964
2801.6593552036 0.0) (11 16674.2081447964 2779.0349208145 0.0))
((0 . "LINE") (100 . "AcDbEntity") (8 . "MASONRY") (62 . 7) (370 . 13) (100 . "AcDbLine") (10 16670.4355656109
1123.679321267 0.0) (11 16738.3088687783 1123.679321267 0.0))
((0 . "LINE") (100 . "AcDbEntity") (8 . "MASONRY") (62 . 7) (370 . 13) (100 . "AcDbLine") (10 16674.2081447964
2858.2204411765 0.0) (11 16674.2081447964 2824.2837895928 0.0))
((0 . "LINE") (100 . "AcDbEntity") (8 . "MASONRY") (62 . 7) (370 . 13) (100 . "AcDbLine") (10 16674.2081447964
2424.5849886878 0.0) (11 16674.2081447964 2413.2727714932 0.0))
((0 . "LINE") (100 . "AcDbEntity") (8 . "MASONRY") (62 . 7) (370 . 13) (100 . "AcDbLine") (10 16766.5921719457
2424.5849886878 0.0) (11 16674.2081447964 2424.5849886878 0.0))
((0 . "LINE") (100 . "AcDbEntity") (8 . "MASONRY") (62 . 7) (370 . 13) (100 . "AcDbLine") (10 16794.8699547511
2041.8552036199 0.0) (11 16674.2081447964 2041.8552036199 0.0))
((0 . "LINE") (100 . "AcDbEntity") (8 . "MASONRY") (62 . 7) (370 . 13) (100 . "AcDbLine") (10 16674.2081447964
2779.0349208145 0.0) (11 16868.4021266968 2779.0349208145 0.0))
((0 . "LINE") (100 . "AcDbEntity") (8 . "MASONRY") (62 . 7) (370 . 13) (100 . "AcDbLine") (10 16685.520361991
1287.7078506787 0.0) (11 16677.9807239819 1287.7078506787 0.0))
((0 . "LINE") (100 . "AcDbEntity") (8 . "MASONRY") (62 . 7) (370 . 13) (100 . "AcDbLine") (10 16687.4066515837
3340.874581448 0.0) (11 16828.8066063348 3340.874581448 0.0))
((0 . "LINE") (100 . "AcDbEntity") (8 . "MASONRY") (62 . 7) (370 . 13) (100 . "AcDbLine") (10 16687.4066515837
3340.874581448 0.0) (11 16687.4066515837 3371.0407239819 0.0))
((0 . "LINE") (100 . "AcDbEntity") (8 . "MASONRY") (62 . 7) (370 . 13) (100 . "AcDbLine") (10 16685.520361991
2109.7285067873 0.0) (11 16719.4570135747 2109.7285067873 0.0))
((0 . "LINE") (100 . "AcDbEntity") (8 . "MASONRY") (62 . 7) (370 . 13) (100 . "AcDbLine") (10 16804.0003733032
651.537861991 0.0) (11 16853.4514705882 651.537861991 0.0))
((0 . "LINE") (100 . "AcDbEntity") (8 . "MASONRY") (62 . 7) (370 . 13) (100 . "AcDbLine") (10 16691.1764705882
3469.0801696833 0.0) (11 16691.1764705882 3442.6845361991 0.0))
((0 . "LINE") (100 . "AcDbEntity") (8 . "MASONRY") (62 . 7) (370 . 13) (100 . "AcDbLine") (10 16691.1764705882
3092.0058031674 0.0) (11 16691.1764705882 3107.089219457 0.0))
((0 . "LINE") (100 . "AcDbEntity") (8 . "MASONRY") (62 . 7) (370 . 13) (100 . "AcDbLine") (10 16691.1764705882
3469.0801696833 0.0) (11 16874.0554751131 3469.0801696833 0.0))
((0 . "LINE") (100 . "AcDbEntity") (8 . "MASONRY") (62 . 7) (370 . 13) (100 . "AcDbLine") (10 16768.4784615385
3107.089219457 0.0) (11 16691.1764705882 3107.089219457 0.0))
((0 . "LINE") (100 . "AcDbEntity") (8 . "MASONRY") (62 . 7) (370 . 13) (100 . "AcDbLine") (10 16693.06 1165.1583710407
0.0) (11 16693.06 1180.2404072398 0.0))
((0 . "LINE") (100 . "AcDbEntity") (8 . "MASONRY") (62 . 7) (370 . 13) (100 . "AcDbLine") (10 16693.06 1180.2404072398
0.0) (11 16874.0554751131 1180.2404072398 0.0))
((0 . "LINE") (100 . "AcDbEntity") (8 . "MASONRY") (62 . 7) (370 . 13) (100 . "AcDbLine") (10 16704.3722171946
2190.1975565611 0.0) (11 16704.3722171946 2263.6524095023 0.0))
((0 . "LINE") (100 . "AcDbEntity") (8 . "MASONRY") (62 . 7) (370 . 13) (100 . "AcDbLine") (10 16704.3722171946
2317.1196153846 0.0) (11 16704.3722171946 2263.6524095023 0.0))
((0 . "LINE") (100 . "AcDbEntity") (8 . "MASONRY") (62 . 7) (370 . 13) (100 . "AcDbLine") (10 16696.8325791855
1248.1150904977 0.0) (11 16825.0395475113 1248.1150904977 0.0))
((0 . "LINE") (100 . "AcDbEntity") (8 . "MASONRY") (62 . 7) (370 . 13) (100 . "AcDbLine") (10 16704.3722171946
2190.1975565611 0.0) (11 16710.0310859729 2190.1975565611 0.0))
((0 . "LINE") (100 . "AcDbEntity") (8 . "MASONRY") (62 . 7) (370 . 13) (100 . "AcDbLine") (10 16704.3722171946
1691.1764705882 0.0) (11 16730.7692307692 1691.1764705882 0.0))
((0 . "LINE") (100 . "AcDbEntity") (8 . "MASONRY") (62 . 7) (370 . 13) (100 . "AcDbLine") (10 17179.4853393665
2317.1196153846 0.0) (11 16704.3722171946 2317.1196153846 0.0))
((0 . "LINE") (100 . "AcDbEntity") (8 . "MASONRY") (62 . 7) (370 . 13) (100 . "AcDbLine") (10 16710.0310859729
2190.1975565611 0.0) (11 16710.0310859729 2171.9457013575 0.0))
((0 . "LINE") (100 . "AcDbEntity") (8 . "MASONRY") (62 . 7) (370 . 13) (100 . "AcDbLine") (10 16909.8784162896
2190.1975565611 0.0) (11 16710.0310859729 2190.1975565611 0.0))
((0 . "LINE") (100 . "AcDbEntity") (8 . "MASONRY") (62 . 7) (370 . 13) (100 . "AcDbLine") (10 16745.8540271493
1461.1609276018 0.0) (11 16711.9173755656 1461.1609276018 0.0))
((0 . "LINE") (100 . "AcDbEntity") (8 . "MASONRY") (62 . 7) (370 . 13) (100 . "AcDbLine") (10 16715.6844343891
2826.1693891403 0.0) (11 16742.0814479638 2826.1693891403 0.0))
((0 . "LINE") (100 . "AcDbEntity") (8 . "MASONRY") (62 . 7) (370 . 13) (100 . "AcDbLine") (10 16713.8009049774
1862.822658371 0.0) (11 16734.5418099548 1862.822658371 0.0))
((0 . "LINE") (100 . "AcDbEntity") (8 . "MASONRY") (62 . 7) (370 . 13) (100 . "AcDbLine") (10 16868.4021266968
2109.7285067873 0.0) (11 16753.3936651584 2109.7285067873 0.0))
((0 . "LINE") (100 . "AcDbEntity") (8 . "MASONRY") (62 . 7) (370 . 13) (100 . "AcDbLine") (10 16755.8074547511
1040.7239819005 0.0) (11 16755.8074547511 1001.1312217195 0.0))
((0 . "LINE") (100 . "AcDbEntity") (8 . "MASONRY") (62 . 7) (370 . 13) (100 . "AcDbLine") (10 16755.8074547511
1001.1312217195 0.0) (11 16783.5577375566 1001.1312217195 0.0))
((0 . "LINE") (100 . "AcDbEntity") (8 . "MASONRY") (62 . 7) (370 . 13) (100 . "AcDbLine") (10 16941.9287782805
1862.7453280543 0.0) (11 16760.9333031674 1862.7453280543 0.0))
((0 . "LINE") (100 . "AcDbEntity") (8 . "MASONRY") (62 . 7) (370 . 13) (100 . "AcDbLine") (10 16763.8359276018
723.9819004525 0.0) (11 16806.1807918552 723.9819004525 0.0))
((0 . "LINE") (100 . "AcDbEntity") (8 . "MASONRY") (62 . 7) (370 . 13) (100 . "AcDbLine") (10 16766.5921719457
2424.5849886878 0.0) (11 16776.0180995475 2424.5849886878 0.0))
((0 . "LINE") (100 . "AcDbEntity") (8 . "MASONRY") (62 . 7) (370 . 13) (100 . "AcDbLine") (10 16776.0180995475
2424.5849886878 0.0) (11 16836.3517647059 2424.5849886878 0.0))
((0 . "LINE") (100 . "AcDbEntity") (8 . "MASONRY") (62 . 7) (370 . 13) (100 . "AcDbLine") (10 16766.5921719457
2424.5849886878 0.0) (11 16766.5921719457 2435.8972058824 0.0))
((0 . "LINE") (100 . "AcDbEntity") (8 . "MASONRY") (62 . 7) (370 . 13) (100 . "AcDbLine") (10 16772.245520362
769.1817533937 0.0) (11 16926.2786425339 769.1817533937 0.0))
((0 . "LINE") (100 . "AcDbEntity") (8 . "MASONRY") (62 . 7) (370 . 13) (100 . "AcDbLine") (10 16968.3257918552
772.8604298643 0.0) (11 17011.6869909502 772.8604298643 0.0))
((0 . "LINE") (100 . "AcDbEntity") (8 . "MASONRY") (62 . 7) (370 . 13) (100 . "AcDbLine") (10 17011.6869909502
772.8604298643 0.0) (11 17011.6869909502 727.751719457 0.0))
((0 . "LINE") (100 . "AcDbEntity") (8 . "MASONRY") (62 . 7) (370 . 13) (100 . "AcDbLine") (10 16776.0180995475
3299.3969117647 0.0) (11 16776.0180995475 3256.1848529412 0.0))
((0 . "LINE") (100 . "AcDbEntity") (8 . "MASONRY") (62 . 7) (370 . 13) (100 . "AcDbLine") (10 17006.0350226244
3256.1848529412 0.0) (11 16776.0180995475 3256.1848529412 0.0))
((0 . "LINE") (100 . "AcDbEntity") (8 . "MASONRY") (62 . 7) (370 . 13) (100 . "AcDbLine") (10 16806.1807918552
723.9819004525 0.0) (11 16806.1807918552 701.4347963801 0.0))
((0 . "LINE") (100 . "AcDbEntity") (8 . "MASONRY") (62 . 7) (370 . 13) (100 . "AcDbLine") (10 16806.1807918552
701.4347963801 0.0) (11 16779.790678733 701.4347963801 0.0))
((0 . "LINE") (100 . "AcDbEntity") (8 . "MASONRY") (62 . 7) (370 . 13) (100 . "AcDbLine") (10 16847.6639819005
2558.4459954751 0.0) (11 16783.5577375566 2558.4459954751 0.0))
((0 . "LINE") (100 . "AcDbEntity") (8 . "MASONRY") (62 . 7) (370 . 13) (100 . "AcDbLine") (10 16792.9864253394
2956.2591968326 0.0) (11 16792.9864253394 2948.718178733 0.0))
((0 . "LINE") (100 . "AcDbEntity") (8 . "MASONRY") (62 . 7) (370 . 13) (100 . "AcDbLine") (10 16817.4943891403
827.6767647059 0.0) (11 16791.1028959276 827.6767647059 0.0))
((0 . "LINE") (100 . "AcDbEntity") (8 . "MASONRY") (62 . 7) (370 . 13) (100 . "AcDbLine") (10 16821.2669683258
3103.318020362 0.0) (11 16798.6425339367 3103.318020362 0.0))
((0 . "LINE") (100 . "AcDbEntity") (8 . "MASONRY") (62 . 7) (370 . 13) (100 . "AcDbLine") (10 16968.3257918552
1681.7505429864 0.0) (11 16813.7273303167 1681.7505429864 0.0))
((0 . "LINE") (100 . "AcDbEntity") (8 . "MASONRY") (62 . 7) (370 . 13) (100 . "AcDbLine") (10 16813.7273303167
1681.7505429864 0.0) (11 16799.2446040724 1681.7505429864 0.0))
((0 . "LINE") (100 . "AcDbEntity") (8 . "MASONRY") (62 . 7) (370 . 13) (100 . "AcDbLine") (10 16799.2446040724
1681.7505429864 0.0) (11 16799.2446040724 1708.1447963801 0.0))
((0 . "LINE") (100 . "AcDbEntity") (8 . "MASONRY") (62 . 7) (370 . 13) (100 . "AcDbLine") (10 16804.2986425339
1600.6787330317 0.0) (11 16804.2986425339 1640.2714932127 0.0))
((0 . "LINE") (100 . "AcDbEntity") (8 . "MASONRY") (62 . 7) (370 . 13) (100 . "AcDbLine") (10 16889.1402714932
991.7052941176 0.0) (11 16802.4151131222 991.7052941176 0.0))
((0 . "LINE") (100 . "AcDbEntity") (8 . "MASONRY") (62 . 7) (370 . 13) (100 . "AcDbLine") (10 16804.2986425339
1600.6787330317 0.0) (11 16817.4943891403 1600.6787330317 0.0))
((0 . "LINE") (100 . "AcDbEntity") (8 . "MASONRY") (62 . 7) (370 . 13) (100 . "AcDbLine") (10 16832.5791855204
2958.1447963801 0.0) (11 16809.9547511312 2958.1447963801 0.0))
((0 . "LINE") (100 . "AcDbEntity") (8 . "MASONRY") (62 . 7) (370 . 13) (100 . "AcDbLine") (10 16809.9547511312
2441.5540045249 0.0) (11 16825.0395475113 2441.5540045249 0.0))
((0 . "LINE") (100 . "AcDbEntity") (8 . "MASONRY") (62 . 7) (370 . 13) (100 . "AcDbLine") (10 16855.2036199095
723.9819004525 0.0) (11 16806.1807918552 723.9819004525 0.0))
((0 . "LINE") (100 . "AcDbEntity") (8 . "MASONRY") (62 . 7) (370 . 13) (100 . "AcDbLine") (10 16825.0395475113
2045.6264027149 0.0) (11 16870.2884162896 2045.6264027149 0.0))
((0 . "LINE") (100 . "AcDbEntity") (8 . "MASONRY") (62 . 7) (370 . 13) (100 . "AcDbLine") (10 16825.0395475113
1815.6108597285 0.0) (11 17024.8868778281 1815.6108597285 0.0))
((0 . "LINE") (100 . "AcDbEntity") (8 . "MASONRY") (62 . 7) (370 . 13) (100 . "AcDbLine") (10 16866.5158371041
1541.0341289593 0.0) (11 16866.5158371041 1466.8916063348 0.0))
((0 . "LINE") (100 . "AcDbEntity") (8 . "MASONRY") (62 . 7) (370 . 13) (100 . "AcDbLine") (10 16866.5158371041
1466.8916063348 0.0) (11 16832.5791855204 1466.8916063348 0.0))
((0 . "LINE") (100 . "AcDbEntity") (8 . "MASONRY") (62 . 7) (370 . 13) (100 . "AcDbLine") (10 16855.2036199095
3101.4324208145 0.0) (11 16911.7647058824 3101.4324208145 0.0))
((0 . "LINE") (100 . "AcDbEntity") (8 . "MASONRY") (62 . 7) (370 . 13) (100 . "AcDbLine") (10 16870.2884162896
2969.4570135747 0.0) (11 16870.2884162896 2956.2591968326 0.0))
((0 . "LINE") (100 . "AcDbEntity") (8 . "MASONRY") (62 . 7) (370 . 13) (100 . "AcDbLine") (10 17162.5197737557
3469.0801696833 0.0) (11 16874.0554751131 3469.0801696833 0.0))
((0 . "LINE") (100 . "AcDbEntity") (8 . "MASONRY") (62 . 7) (370 . 13) (100 . "AcDbLine") (10 16874.0554751131
3525.6412556561 0.0) (11 16874.0554751131 3469.0801696833 0.0))
((0 . "LINE") (100 . "AcDbEntity") (8 . "MASONRY") (62 . 7) (370 . 13) (100 . "AcDbLine") (10 16868.4021266968
2779.0349208145 0.0) (11 17175.718280543 2779.0349208145 0.0))
((0 . "LINE") (100 . "AcDbEntity") (8 . "MASONRY") (62 . 7) (370 . 13) (100 . "AcDbLine") (10 16868.4021266968
2760.1809954751 0.0) (11 16868.4021266968 2779.0349208145 0.0))
((0 . "LINE") (100 . "AcDbEntity") (8 . "MASONRY") (62 . 7) (370 . 13) (100 . "AcDbLine") (10 16870.2884162896
2633.8616968326 0.0) (11 16894.7963800905 2633.8616968326 0.0))
((0 . "LINE") (100 . "AcDbEntity") (8 . "MASONRY") (62 . 7) (370 . 13) (100 . "AcDbLine") (10 16870.2884162896
2633.8616968326 0.0) (11 16870.2884162896 2718.7033257919 0.0))
((0 . "LINE") (100 . "AcDbEntity") (8 . "MASONRY") (62 . 7) (370 . 13) (100 . "AcDbLine") (10 16868.4021266968
2070.1357466063 0.0) (11 16868.4021266968 2109.7285067873 0.0))
((0 . "LINE") (100 . "AcDbEntity") (8 . "MASONRY") (62 . 7) (370 . 13) (100 . "AcDbLine") (10 16868.4021266968
2109.7285067873 0.0) (11 16909.8784162896 2109.7285067873 0.0))
((0 . "LINE") (100 . "AcDbEntity") (8 . "MASONRY") (62 . 7) (370 . 13) (100 . "AcDbLine") (10 16870.2884162896
2011.6897511312 0.0) (11 16870.2884162896 2045.6264027149 0.0))
((0 . "LINE") (100 . "AcDbEntity") (8 . "MASONRY") (62 . 7) (370 . 13) (100 . "AcDbLine") (10 16870.2884162896
2045.6264027149 0.0) (11 16870.2884162896 2058.8235294118 0.0))
((0 . "LINE") (100 . "AcDbEntity") (8 . "MASONRY") (62 . 7) (370 . 13) (100 . "AcDbLine") (10 16866.5158371041
1541.0341289593 0.0) (11 16866.5158371041 1594.9121493213 0.0))
((0 . "LINE") (100 . "AcDbEntity") (8 . "MASONRY") (62 . 7) (370 . 13) (100 . "AcDbLine") (10 16866.5158371041
1594.9121493213 0.0) (11 16957.0135746606 1594.9121493213 0.0))
((0 . "LINE") (100 . "AcDbEntity") (8 . "MASONRY") (62 . 7) (370 . 13) (100 . "AcDbLine") (10 16874.0554751131
1255.6561085973 0.0) (11 16874.0554751131 1236.8028733032 0.0))
((0 . "LINE") (100 . "AcDbEntity") (8 . "MASONRY") (62 . 7) (370 . 13) (100 . "AcDbLine") (10 16889.1402714932
3342.7601809955 0.0) (11 16870.2884162896 3342.7601809955 0.0))
((0 . "LINE") (100 . "AcDbEntity") (8 . "MASONRY") (62 . 7) (370 . 13) (100 . "AcDbLine") (10 16870.2884162896
2969.4570135747 0.0) (11 16870.2884162896 3001.5080656109 0.0))
((0 . "LINE") (100 . "AcDbEntity") (8 . "MASONRY") (62 . 7) (370 . 13) (100 . "AcDbLine") (10 17183.257918552
2969.4570135747 0.0) (11 16870.2884162896 2969.4570135747 0.0))
((0 . "LINE") (100 . "AcDbEntity") (8 . "MASONRY") (62 . 7) (370 . 13) (100 . "AcDbLine") (10 16870.2884162896
2922.3225452489 0.0) (11 16870.2884162896 2895.92760181 0.0))
((0 . "LINE") (100 . "AcDbEntity") (8 . "MASONRY") (62 . 7) (370 . 13) (100 . "AcDbLine") (10 17179.4853393665
2895.92760181 0.0) (11 16870.2884162896 2895.92760181 0.0))
((0 . "LINE") (100 . "AcDbEntity") (8 . "MASONRY") (62 . 7) (370 . 13) (100 . "AcDbLine") (10 16949.4739366516
2718.7033257919 0.0) (11 16870.2884162896 2718.7033257919 0.0))
((0 . "LINE") (100 . "AcDbEntity") (8 . "MASONRY") (62 . 7) (370 . 13) (100 . "AcDbLine") (10 16870.2884162896
2558.4459954751 0.0) (11 16892.9128506787 2558.4459954751 0.0))
((0 . "LINE") (100 . "AcDbEntity") (8 . "MASONRY") (62 . 7) (370 . 13) (100 . "AcDbLine") (10 16881.5978733032
2418.9295701357 0.0) (11 16870.2884162896 2418.9295701357 0.0))
((0 . "LINE") (100 . "AcDbEntity") (8 . "MASONRY") (62 . 7) (370 . 13) (100 . "AcDbLine") (10 16870.2884162896
2011.6897511312 0.0) (11 16885.3676923077 2011.6897511312 0.0))
((0 . "LINE") (100 . "AcDbEntity") (8 . "MASONRY") (62 . 7) (370 . 13) (100 . "AcDbLine") (10 16870.2884162896
2011.6897511312 0.0) (11 16870.2884162896 1987.1797171946 0.0))
((0 . "LINE") (100 . "AcDbEntity") (8 . "MASONRY") (62 . 7) (370 . 13) (100 . "AcDbLine") (10 16870.2884162896
1955.1286651584 0.0) (11 16870.2884162896 1968.3257918552 0.0))
((0 . "LINE") (100 . "AcDbEntity") (8 . "MASONRY") (62 . 7) (370 . 13) (100 . "AcDbLine") (10 16870.2884162896
1955.1286651584 0.0) (11 16987.1776470588 1955.1286651584 0.0))
((0 . "LINE") (100 . "AcDbEntity") (8 . "MASONRY") (62 . 7) (370 . 13) (100 . "AcDbLine") (10 16874.6603054299
829.5616742081 0.0) (11 16874.6603054299 901.0522058824 0.0))
((0 . "LINE") (100 . "AcDbEntity") (8 . "MASONRY") (62 . 7) (370 . 13) (100 . "AcDbLine") (10 16874.6603054299
901.0522058824 0.0) (11 16892.9128506787 901.0522058824 0.0))
((0 . "LINE") (100 . "AcDbEntity") (8 . "MASONRY") (62 . 7) (370 . 13) (100 . "AcDbLine") (10 16892.9128506787
901.0522058824 0.0) (11 16941.9287782805 901.0522058824 0.0))
((0 . "LINE") (100 . "AcDbEntity") (8 . "MASONRY") (62 . 7) (370 . 13) (100 . "AcDbLine") (10 16874.0554751131
3525.6412556561 0.0) (11 16874.0554751131 3536.9534728507 0.0))
((0 . "LINE") (100 . "AcDbEntity") (8 . "MASONRY") (62 . 7) (370 . 13) (100 . "AcDbLine") (10 16881.5978733032
2418.9295701357 0.0) (11 16881.5978733032 2439.6684049774 0.0))
((0 . "LINE") (100 . "AcDbEntity") (8 . "MASONRY") (62 . 7) (370 . 13) (100 . "AcDbLine") (10 17183.257918552
1322.1720022624 0.0) (11 16949.4739366516 1322.1720022624 0.0))
((0 . "LINE") (100 . "AcDbEntity") (8 . "MASONRY") (62 . 7) (370 . 13) (100 . "AcDbLine") (10 16949.4739366516
1322.1720022624 0.0) (11 16911.7647058824 1322.1720022624 0.0))
((0 . "LINE") (100 . "AcDbEntity") (8 . "MASONRY") (62 . 7) (370 . 13) (100 . "AcDbLine") (10 16911.7647058824
1322.1720022624 0.0) (11 16876.0190950226 1322.1720022624 0.0))
((0 . "LINE") (100 . "AcDbEntity") (8 . "MASONRY") (62 . 7) (370 . 13) (100 . "AcDbLine") (10 16876.0190950226
1322.1720022624 0.0) (11 16876.0190950226 1331.0718099548 0.0))
((0 . "LINE") (100 . "AcDbEntity") (8 . "MASONRY") (62 . 7) (370 . 13) (100 . "AcDbLine") (10 16881.6006334842
1331.0718099548 0.0) (11 16876.0190950226 1331.0718099548 0.0))
((0 . "LINE") (100 . "AcDbEntity") (8 . "MASONRY") (62 . 7) (370 . 13) (100 . "AcDbLine") (10 17179.4853393665
1180.2404072398 0.0) (11 16874.0554751131 1180.2404072398 0.0))
((0 . "LINE") (100 . "AcDbEntity") (8 . "MASONRY") (62 . 7) (370 . 13) (100 . "AcDbLine") (10 16874.0554751131
1236.8028733032 0.0) (11 16874.0554751131 1180.2404072398 0.0))
((0 . "LINE") (100 . "AcDbEntity") (8 . "MASONRY") (62 . 7) (370 . 13) (100 . "AcDbLine") (10 17183.257918552
3525.6412556561 0.0) (11 16874.0554751131 3525.6412556561 0.0))
((0 . "LINE") (100 . "AcDbEntity") (8 . "MASONRY") (62 . 7) (370 . 13) (100 . "AcDbLine") (10 16874.0554751131
1236.8028733032 0.0) (11 17183.257918552 1236.8028733032 0.0))
((0 . "LINE") (100 . "AcDbEntity") (8 . "MASONRY") (62 . 7) (370 . 13) (100 . "AcDbLine") (10 16881.5978733032
2418.9295701357 0.0) (11 17011.6938914027 2418.9295701357 0.0))
((0 . "LINE") (100 . "AcDbEntity") (8 . "MASONRY") (62 . 7) (370 . 13) (100 . "AcDbLine") (10 16889.1402714932
939.0686877828 0.0) (11 16889.1402714932 991.7052941176 0.0))
((0 . "LINE") (100 . "AcDbEntity") (8 . "MASONRY") (62 . 7) (370 . 13) (100 . "AcDbLine") (10 16896.6799095023
991.7052941176 0.0) (11 16889.1402714932 991.7052941176 0.0))
((0 . "LINE") (100 . "AcDbEntity") (8 . "MASONRY") (62 . 7) (370 . 13) (100 . "AcDbLine") (10 16889.1402714932
939.0686877828 0.0) (11 16943.7101244344 939.0686877828 0.0))
((0 . "LINE") (100 . "AcDbEntity") (8 . "MASONRY") (62 . 7) (370 . 13) (100 . "AcDbLine") (10 16943.7101244344
939.0686877828 0.0) (11 16943.7101244344 987.8567647059 0.0))
((0 . "LINE") (100 . "AcDbEntity") (8 . "MASONRY") (62 . 7) (370 . 13) (100 . "AcDbLine") (10 16943.7101244344
987.8567647059 0.0) (11 17179.4853393665 987.8567647059 0.0))
((0 . "LINE") (100 . "AcDbEntity") (8 . "MASONRY") (62 . 7) (370 . 13) (100 . "AcDbLine") (10 16891.6286312217
3427.6018099548 0.0) (11 16891.6286312217 3386.1269004525 0.0))
((0 . "LINE") (100 . "AcDbEntity") (8 . "MASONRY") (62 . 7) (370 . 13) (100 . "AcDbLine") (10 16891.6286312217
3386.1269004525 0.0) (11 16911.7647058824 3386.1269004525 0.0))
((0 . "LINE") (100 . "AcDbEntity") (8 . "MASONRY") (62 . 7) (370 . 13) (100 . "AcDbLine") (10 16894.7963800905
2594.2682466063 0.0) (11 16894.7963800905 2633.8616968326 0.0))
((0 . "LINE") (100 . "AcDbEntity") (8 . "MASONRY") (62 . 7) (370 . 13) (100 . "AcDbLine") (10 16892.9128506787
2537.7071606335 0.0) (11 16892.9128506787 2509.4273076923 0.0))
((0 . "LINE") (100 . "AcDbEntity") (8 . "MASONRY") (62 . 7) (370 . 13) (100 . "AcDbLine") (10 17007.9185520362
2509.4273076923 0.0) (11 16892.9128506787 2509.4273076923 0.0))
((0 . "LINE") (100 . "AcDbEntity") (8 . "MASONRY") (62 . 7) (370 . 13) (100 . "AcDbLine") (10 16904.2250678733
2633.8616968326 0.0) (11 16894.7963800905 2633.8616968326 0.0))
((0 . "LINE") (100 . "AcDbEntity") (8 . "MASONRY") (62 . 7) (370 . 13) (100 . "AcDbLine") (10 16909.8784162896
2190.1975565611 0.0) (11 16909.8784162896 2109.7285067873 0.0))
((0 . "LINE") (100 . "AcDbEntity") (8 . "MASONRY") (62 . 7) (370 . 13) (100 . "AcDbLine") (10 16909.8784162896
2190.1975565611 0.0) (11 16981.5242986425 2190.1975565611 0.0))
((0 . "LINE") (100 . "AcDbEntity") (8 . "MASONRY") (62 . 7) (370 . 13) (100 . "AcDbLine") (10 16909.8784162896
2109.7285067873 0.0) (11 17179.4853393665 2109.7285067873 0.0))
((0 . "LINE") (100 . "AcDbEntity") (8 . "MASONRY") (62 . 7) (370 . 13) (100 . "AcDbLine") (10 16923.0769230769
3376.6968325792 0.0) (11 17066.3631674208 3376.6968325792 0.0))
((0 . "LINE") (100 . "AcDbEntity") (8 . "MASONRY") (62 . 7) (370 . 13) (100 . "AcDbLine") (10 16923.0769230769
3103.318020362 0.0) (11 16979.6380090498 3103.318020362 0.0))
((0 . "LINE") (100 . "AcDbEntity") (8 . "MASONRY") (62 . 7) (370 . 13) (100 . "AcDbLine") (10 17006.0350226244
3337.1040723982 0.0) (11 16926.8495022624 3337.1040723982 0.0))
((0 . "LINE") (100 . "AcDbEntity") (8 . "MASONRY") (62 . 7) (370 . 13) (100 . "AcDbLine") (10 17028.6594570136
3050.5281334842 0.0) (11 16930.616561086 3050.5281334842 0.0))
((0 . "LINE") (100 . "AcDbEntity") (8 . "MASONRY") (62 . 7) (370 . 13) (100 . "AcDbLine") (10 16945.7013574661
2631.9760972851 0.0) (11 17039.9716742081 2631.9760972851 0.0))
((0 . "LINE") (100 . "AcDbEntity") (8 . "MASONRY") (62 . 7) (370 . 13) (100 . "AcDbLine") (10 17036.1990950226
2607.4660633484 0.0) (11 16949.4739366516 2607.4660633484 0.0))
((0 . "LINE") (100 . "AcDbEntity") (8 . "MASONRY") (62 . 7) (370 . 13) (100 . "AcDbLine") (10 17011.6869909502
727.751719457 0.0) (11 16968.3257918552 727.751719457 0.0))
((0 . "LINE") (100 . "AcDbEntity") (8 . "MASONRY") (62 . 7) (370 . 13) (100 . "AcDbLine") (10 16957.0135746606
1594.9121493213 0.0) (11 16957.0135746606 1628.9592760181 0.0))
((0 . "LINE") (100 . "AcDbEntity") (8 . "MASONRY") (62 . 7) (370 . 13) (100 . "AcDbLine") (10 17130.4666515837
1594.9121493213 0.0) (11 16957.0135746606 1594.9121493213 0.0))
((0 . "LINE") (100 . "AcDbEntity") (8 . "MASONRY") (62 . 7) (370 . 13) (100 . "AcDbLine") (10 16998.4898642534
584.4654751131 0.0) (11 16972.0983710407 584.4654751131 0.0))
((0 . "LINE") (100 . "AcDbEntity") (8 . "MASONRY") (62 . 7) (370 . 13) (100 . "AcDbLine") (10 16972.0983710407
573.1532579186 0.0) (11 16972.0983710407 584.4654751131 0.0))
((0 . "LINE") (100 . "AcDbEntity") (8 . "MASONRY") (62 . 7) (370 . 13) (100 . "AcDbLine") (10 16977.751719457
2281.2973642534 0.0) (11 16977.751719457 2262.443438914 0.0))
((0 . "LINE") (100 . "AcDbEntity") (8 . "MASONRY") (62 . 7) (370 . 13) (100 . "AcDbLine") (10 17175.718280543
2726.2443438914 0.0) (11 16979.6380090498 2726.2443438914 0.0))
((0 . "LINE") (100 . "AcDbEntity") (8 . "MASONRY") (62 . 7) (370 . 13) (100 . "AcDbLine") (10 16981.5242986425
2190.1975565611 0.0) (11 17017.347239819 2190.1975565611 0.0))
((0 . "LINE") (100 . "AcDbEntity") (8 . "MASONRY") (62 . 7) (370 . 13) (100 . "AcDbLine") (10 16981.5242986425
2190.1975565611 0.0) (11 16981.5242986425 2205.8823529412 0.0))
((0 . "LINE") (100 . "AcDbEntity") (8 . "MASONRY") (62 . 7) (370 . 13) (100 . "AcDbLine") (10 16983.4105882353
2239.8190045249 0.0) (11 16983.4105882353 2224.7362782805 0.0))
((0 . "LINE") (100 . "AcDbEntity") (8 . "MASONRY") (62 . 7) (370 . 13) (100 . "AcDbLine") (10 16983.4105882353
1892.910780543 0.0) (11 16983.4105882353 1900.4524886878 0.0))
((0 . "LINE") (100 . "AcDbEntity") (8 . "MASONRY") (62 . 7) (370 . 13) (100 . "AcDbLine") (10 16983.4105882353
1858.9741289593 0.0) (11 16990.9502262443 1858.9741289593 0.0))
((0 . "LINE") (100 . "AcDbEntity") (8 . "MASONRY") (62 . 7) (370 . 13) (100 . "AcDbLine") (10 16994.7228054299
1674.2081447964 0.0) (11 16983.4105882353 1674.2081447964 0.0))
((0 . "LINE") (100 . "AcDbEntity") (8 . "MASONRY") (62 . 7) (370 . 13) (100 . "AcDbLine") (10 17183.257918552
1955.1286651584 0.0) (11 16987.1776470588 1955.1286651584 0.0))
((0 . "LINE") (100 . "AcDbEntity") (8 . "MASONRY") (62 . 7) (370 . 13) (100 . "AcDbLine") (10 16987.1776470588
1938.1596493213 0.0) (11 16987.1776470588 1955.1286651584 0.0))
((0 . "LINE") (100 . "AcDbEntity") (8 . "MASONRY") (62 . 7) (370 . 13) (100 . "AcDbLine") (10 17006.0350226244
3337.1040723982 0.0) (11 17006.0350226244 3256.1848529412 0.0))
((0 . "LINE") (100 . "AcDbEntity") (8 . "MASONRY") (62 . 7) (370 . 13) (100 . "AcDbLine") (10 17006.0350226244
3337.1040723982 0.0) (11 17183.257918552 3337.1040723982 0.0))
((0 . "LINE") (100 . "AcDbEntity") (8 . "MASONRY") (62 . 7) (370 . 13) (100 . "AcDbLine") (10 17006.0350226244
3256.1848529412 0.0) (11 17032.4265158371 3256.1848529412 0.0))
((0 . "LINE") (100 . "AcDbEntity") (8 . "MASONRY") (62 . 7) (370 . 13) (100 . "AcDbLine") (10 17032.4265158371
3256.1848529412 0.0) (11 17183.257918552 3256.1848529412 0.0))
((0 . "LINE") (100 . "AcDbEntity") (8 . "MASONRY") (62 . 7) (370 . 13) (100 . "AcDbLine") (10 17007.9185520362
2509.4273076923 0.0) (11 17007.9185520362 2488.6877828054 0.0))
((0 . "LINE") (100 . "AcDbEntity") (8 . "MASONRY") (62 . 7) (370 . 13) (100 . "AcDbLine") (10 17024.8868778281
2418.9295701357 0.0) (11 17011.6938914027 2418.9295701357 0.0))
((0 . "LINE") (100 . "AcDbEntity") (8 . "MASONRY") (62 . 7) (370 . 13) (100 . "AcDbLine") (10 17134.2364705882
2450.9032918552 0.0) (11 17011.6938914027 2450.9032918552 0.0))
((0 . "LINE") (100 . "AcDbEntity") (8 . "MASONRY") (62 . 7) (370 . 13) (100 . "AcDbLine") (10 17011.6938914027
2450.9032918552 0.0) (11 17011.6938914027 2418.9295701357 0.0))
((0 . "LINE") (100 . "AcDbEntity") (8 . "MASONRY") (62 . 7) (370 . 13) (100 . "AcDbLine") (10 17007.9185520362
2509.4273076923 0.0) (11 17175.718280543 2509.4273076923 0.0))
((0 . "LINE") (100 . "AcDbEntity") (8 . "MASONRY") (62 . 7) (370 . 13) (100 . "AcDbLine") (10 17009.802081448
1434.7666742081 0.0) (11 17009.802081448 1417.7969683258 0.0))
((0 . "LINE") (100 . "AcDbEntity") (8 . "MASONRY") (62 . 7) (370 . 13) (100 . "AcDbLine") (10 17009.802081448
1434.7666742081 0.0) (11 17130.4666515837 1434.7666742081 0.0))
((0 . "LINE") (100 . "AcDbEntity") (8 . "MASONRY") (62 . 7) (370 . 13) (100 . "AcDbLine") (10 17017.347239819
1380.0904977376 0.0) (11 17017.347239819 1365.0084615385 0.0))
((0 . "LINE") (100 . "AcDbEntity") (8 . "MASONRY") (62 . 7) (370 . 13) (100 . "AcDbLine") (10 17126.6968325792
727.751719457 0.0) (11 17011.6869909502 727.751719457 0.0))
((0 . "LINE") (100 . "AcDbEntity") (8 . "MASONRY") (62 . 7) (370 . 13) (100 . "AcDbLine") (10 17024.8868778281
554.2986425339 0.0) (11 17024.8868778281 524.1318099548 0.0))
((0 . "LINE") (100 . "AcDbEntity") (8 . "MASONRY") (62 . 7) (370 . 13) (100 . "AcDbLine") (10 17021.1142986425
3099.5475113122 0.0) (11 17081.4479638009 3099.5475113122 0.0))
((0 . "LINE") (100 . "AcDbEntity") (8 . "MASONRY") (62 . 7) (370 . 13) (100 . "AcDbLine") (10 17021.1142986425
822.0220361991 0.0) (11 17179.4853393665 822.0220361991 0.0))
((0 . "LINE") (100 . "AcDbEntity") (8 . "MASONRY") (62 . 7) (370 . 13) (100 . "AcDbLine") (10 17028.6594570136
3050.5281334842 0.0) (11 17028.6594570136 3069.3813687783 0.0))
((0 . "LINE") (100 . "AcDbEntity") (8 . "MASONRY") (62 . 7) (370 . 13) (100 . "AcDbLine") (10 17028.6594570136
3050.5281334842 0.0) (11 17179.4853393665 3050.5281334842 0.0))
((0 . "LINE") (100 . "AcDbEntity") (8 . "MASONRY") (62 . 7) (370 . 13) (100 . "AcDbLine") (10 17062.5961085973
586.3503846154 0.0) (11 17036.1990950226 586.3503846154 0.0))
((0 . "LINE") (100 . "AcDbEntity") (8 . "MASONRY") (62 . 7) (370 . 13) (100 . "AcDbLine") (10 17043.7387330317
2417.0439705882 0.0) (11 17092.7601809955 2417.0439705882 0.0))
((0 . "LINE") (100 . "AcDbEntity") (8 . "MASONRY") (62 . 7) (370 . 13) (100 . "AcDbLine") (10 17153.0938461538
1078.4318325792 0.0) (11 17075.7918552036 1078.4318325792 0.0))
((0 . "LINE") (100 . "AcDbEntity") (8 . "MASONRY") (62 . 7) (370 . 13) (100 . "AcDbLine") (10 17075.7918552036
1104.8274660633 0.0) (11 17075.7918552036 1078.4318325792 0.0))
((0 . "LINE") (100 . "AcDbEntity") (8 . "MASONRY") (62 . 7) (370 . 13) (100 . "AcDbLine") (10 17092.7601809955
2631.9760972851 0.0) (11 17077.6753846154 2631.9760972851 0.0))
((0 . "LINE") (100 . "AcDbEntity") (8 . "MASONRY") (62 . 7) (370 . 13) (100 . "AcDbLine") (10 17077.6753846154
1823.1518778281 0.0) (11 17175.718280543 1823.1518778281 0.0))
((0 . "LINE") (100 . "AcDbEntity") (8 . "MASONRY") (62 . 7) (370 . 13) (100 . "AcDbLine") (10 17077.6753846154
531.6742081448 0.0) (11 17175.718280543 531.6742081448 0.0))
((0 . "LINE") (100 . "AcDbEntity") (8 . "MASONRY") (62 . 7) (370 . 13) (100 . "AcDbLine") (10 17179.4853393665
2009.8041515837 0.0) (11 17081.4479638009 2009.8041515837 0.0))
((0 . "LINE") (100 . "AcDbEntity") (8 . "MASONRY") (62 . 7) (370 . 13) (100 . "AcDbLine") (10 17179.4853393665
584.4654751131 0.0) (11 17107.8449773756 584.4654751131 0.0))
((0 . "LINE") (100 . "AcDbEntity") (8 . "MASONRY") (62 . 7) (370 . 13) (100 . "AcDbLine") (10 17130.4694117647
3099.5475113122 0.0) (11 17111.6120361991 3099.5475113122 0.0))
((0 . "LINE") (100 . "AcDbEntity") (8 . "MASONRY") (62 . 7) (370 . 13) (100 . "AcDbLine") (10 17134.2364705882
2417.0439705882 0.0) (11 17122.9242533937 2417.0439705882 0.0))
((0 . "LINE") (100 . "AcDbEntity") (8 . "MASONRY") (62 . 7) (370 . 13) (100 . "AcDbLine") (10 17130.4666515837
1594.9121493213 0.0) (11 17130.4666515837 1493.2126696833 0.0))
((0 . "LINE") (100 . "AcDbEntity") (8 . "MASONRY") (62 . 7) (370 . 13) (100 . "AcDbLine") (10 17130.4666515837
1493.2126696833 0.0) (11 17130.4666515837 1478.1292533937 0.0))
((0 . "LINE") (100 . "AcDbEntity") (8 . "MASONRY") (62 . 7) (370 . 13) (100 . "AcDbLine") (10 17179.4853393665
1594.9121493213 0.0) (11 17130.4666515837 1594.9121493213 0.0))
((0 . "LINE") (100 . "AcDbEntity") (8 . "MASONRY") (62 . 7) (370 . 13) (100 . "AcDbLine") (10 17126.6968325792
2631.9760972851 0.0) (11 17179.4853393665 2631.9760972851 0.0))
((0 . "LINE") (100 . "AcDbEntity") (8 . "MASONRY") (62 . 7) (370 . 13) (100 . "AcDbLine") (10 17130.4694117647
3182.799739819 0.0) (11 17130.4694117647 3152.3380882353 0.0))
((0 . "LINE") (100 . "AcDbEntity") (8 . "MASONRY") (62 . 7) (370 . 13) (100 . "AcDbLine") (10 17130.4694117647
3182.799739819 0.0) (11 17183.257918552 3182.799739819 0.0))
((0 . "LINE") (100 . "AcDbEntity") (8 . "MASONRY") (62 . 7) (370 . 13) (100 . "AcDbLine") (10 17130.4694117647
3129.7136538462 0.0) (11 17130.4694117647 3099.5475113122 0.0))
((0 . "LINE") (100 . "AcDbEntity") (8 . "MASONRY") (62 . 7) (370 . 13) (100 . "AcDbLine") (10 17145.5486877828
3099.5475113122 0.0) (11 17130.4694117647 3099.5475113122 0.0))
((0 . "LINE") (100 . "AcDbEntity") (8 . "MASONRY") (62 . 7) (370 . 13) (100 . "AcDbLine") (10 17179.4853393665
2611.2372624434 0.0) (11 17134.2364705882 2611.2372624434 0.0))
((0 . "LINE") (100 . "AcDbEntity") (8 . "MASONRY") (62 . 7) (370 . 13) (100 . "AcDbLine") (10 17134.2364705882
2417.0439705882 0.0) (11 17134.2364705882 2450.9032918552 0.0))
((0 . "LINE") (100 . "AcDbEntity") (8 . "MASONRY") (62 . 7) (370 . 13) (100 . "AcDbLine") (10 17134.2364705882
2488.6877828054 0.0) (11 17134.2364705882 2450.9032918552 0.0))
((0 . "LINE") (100 . "AcDbEntity") (8 . "MASONRY") (62 . 7) (370 . 13) (100 . "AcDbLine") (10 17153.0938461538
2417.0439705882 0.0) (11 17134.2364705882 2417.0439705882 0.0))
((0 . "LINE") (100 . "AcDbEntity") (8 . "MASONRY") (62 . 7) (370 . 13) (100 . "AcDbLine") (10 17130.4666515837
1434.7666742081 0.0) (11 17130.4666515837 1478.1292533937 0.0))
((0 . "LINE") (100 . "AcDbEntity") (8 . "MASONRY") (62 . 7) (370 . 13) (100 . "AcDbLine") (10 17153.0938461538
1478.1292533937 0.0) (11 17130.4666515837 1478.1292533937 0.0))
((0 . "LINE") (100 . "AcDbEntity") (8 . "MASONRY") (62 . 7) (370 . 13) (100 . "AcDbLine") (10 17175.718280543
1434.7666742081 0.0) (11 17130.4666515837 1434.7666742081 0.0))
((0 . "LINE") (100 . "AcDbEntity") (8 . "MASONRY") (62 . 7) (370 . 13) (100 . "AcDbLine") (10 17162.5197737557
3469.0801696833 0.0) (11 17179.4853393665 3469.0801696833 0.0))
((0 . "LINE") (100 . "AcDbEntity") (8 . "MASONRY") (62 . 7) (370 . 13) (100 . "AcDbLine") (10 17162.5197737557
3469.0801696833 0.0) (11 17162.5197737557 3487.9334049774 0.0))
((0 . "LINE") (100 . "AcDbEntity") (8 . "MASONRY") (62 . 7) (370 . 13) (100 . "AcDbLine") (10 17175.718280543
729.6380090498 0.0) (11 17168.1731221719 729.6380090498 0.0))
((0 . "LINE") (100 . "AcDbEntity") (8 . "MASONRY") (62 . 7) (370 . 13) (100 . "AcDbLine") (10 17183.257918552
2816.742081448 0.0) (11 17175.718280543 2816.742081448 0.0))
((0 . "LINE") (100 . "AcDbEntity") (8 . "MASONRY") (62 . 7) (370 . 13) (100 . "AcDbLine") (10 17228.5067873303
1087.319219457 0.0) (11 17209.6549321267 1087.319219457 0.0))
((0 . "ARC") (100 . "AcDbEntity") (8 . "WINDOWS") (62 . 7) (370 . 13) (100 . "AcDbCircle") (10 5441.1764705882
3850.6787330317 0.0) (40 . 1420.814479638) (100 . "AcDbArc") (50 . 0.9986934434) (51 . 2.1428992102))
((0 . "ARC") (100 . "AcDbEntity") (8 . "WINDOWS") (62 . 7) (370 . 13) (100 . "AcDbCircle") (10 5446.8325791855
3611.8966817496 0.0) (40 . 1557.7865761689) (100 . "AcDbArc") (50 . 1.0997063654) (51 . 2.0418862882))
((0 . "ARC") (100 . "AcDbEntity") (8 . "WINDOWS") (62 . 7) (370 . 13) (100 . "AcDbCircle") (10 5446.8325791855
3420.8851809955 0.0) (40 . 1680.9247737557) (100 . "AcDbArc") (50 . 1.16615307) (51 . 1.5472399948))
((0 . "ARC") (100 . "AcDbEntity") (8 . "WINDOWS") (62 . 7) (370 . 13) (100 . "AcDbCircle") (10 5446.8325791855
3420.8851809955 0.0) (40 . 1680.9247737557) (100 . "AcDbArc") (50 . 1.5472399948) (51 . 1.5943526588))
((0 . "ARC") (100 . "AcDbEntity") (8 . "WINDOWS") (62 . 7) (370 . 13) (100 . "AcDbCircle") (10 5446.8325791855
3420.8851809955 0.0) (40 . 1680.9247737557) (100 . "AcDbArc") (50 . 1.5943526588) (51 . 1.9754395836))
((0 . "ARC") (100 . "AcDbEntity") (8 . "WINDOWS") (62 . 7) (370 . 13) (100 . "AcDbCircle") (10 5435.520361991
1213.1763763198 0.0) (40 . 1241.574754902) (100 . "AcDbArc") (50 . 0.896796493) (51 . 2.2447961606))
((0 . "ARC") (100 . "AcDbEntity") (8 . "WINDOWS") (62 . 7) (370 . 13) (100 . "AcDbCircle") (10 5441.1764705882
1139.9886877828 0.0) (40 . 1235.5769230769) (100 . "AcDbArc") (50 . 0.9560013805) (51 . 2.185591273))
((0 . "ARC") (100 . "AcDbEntity") (8 . "WINDOWS") (62 . 7) (370 . 13) (100 . "AcDbCircle") (10 5441.1764705882
1112.0537958773 0.0) (40 . 1195.638511815) (100 . "AcDbArc") (50 . 0.978566035) (51 . 1.5329423463))
((0 . "ARC") (100 . "AcDbEntity") (8 . "WINDOWS") (62 . 7) (370 . 13) (100 . "AcDbCircle") (10 5441.1764705882
1112.0537958773 0.0) (40 . 1195.638511815) (100 . "AcDbArc") (50 . 1.5329423463) (51 . 1.599183845))
((0 . "ARC") (100 . "AcDbEntity") (8 . "WINDOWS") (62 . 7) (370 . 13) (100 . "AcDbCircle") (10 5441.1764705882
1112.0537958773 0.0) (40 . 1195.638511815) (100 . "AcDbArc") (50 . 1.599183845) (51 . 2.1630266185))
((0 . "ARC") (100 . "AcDbEntity") (8 . "WINDOWS") (62 . 7) (370 . 13) (100 . "AcDbCircle") (10 14592.7601809955
3850.6787330317 0.0) (40 . 1420.814479638) (100 . "AcDbArc") (50 . 0.9986934434) (51 . 2.1428992102))
((0 . "ARC") (100 . "AcDbEntity") (8 . "WINDOWS") (62 . 7) (370 . 13) (100 . "AcDbCircle") (10 14598.4162895928
3611.8966817496 0.0) (40 . 1557.7865761689) (100 . "AcDbArc") (50 . 1.0997063654) (51 . 2.0418862882))
((0 . "ARC") (100 . "AcDbEntity") (8 . "WINDOWS") (62 . 7) (370 . 13) (100 . "AcDbCircle") (10 14598.4162895928
3420.8851809955 0.0) (40 . 1680.9247737557) (100 . "AcDbArc") (50 . 1.16615307) (51 . 1.5472399948))
((0 . "ARC") (100 . "AcDbEntity") (8 . "WINDOWS") (62 . 7) (370 . 13) (100 . "AcDbCircle") (10 14598.4162895928
3420.8851809955 0.0) (40 . 1680.9247737557) (100 . "AcDbArc") (50 . 1.5472399948) (51 . 1.5943526588))
((0 . "ARC") (100 . "AcDbEntity") (8 . "WINDOWS") (62 . 7) (370 . 13) (100 . "AcDbCircle") (10 14598.4162895928
3420.8851809955 0.0) (40 . 1680.9247737557) (100 . "AcDbArc") (50 . 1.5943526588) (51 . 1.9754395836))
((0 . "ARC") (100 . "AcDbEntity") (8 . "WINDOWS") (62 . 7) (370 . 13) (100 . "AcDbCircle") (10 14587.1040723982
1213.1763763198 0.0) (40 . 1241.574754902) (100 . "AcDbArc") (50 . 0.896796493) (51 . 2.2447961606))
((0 . "ARC") (100 . "AcDbEntity") (8 . "WINDOWS") (62 . 7) (370 . 13) (100 . "AcDbCircle") (10 14592.7601809955
1139.9886877828 0.0) (40 . 1235.5769230769) (100 . "AcDbArc") (50 . 0.9560013805) (51 . 2.185591273))
((0 . "ARC") (100 . "AcDbEntity") (8 . "WINDOWS") (62 . 7) (370 . 13) (100 . "AcDbCircle") (10 14592.7601809955
1112.0537958773 0.0) (40 . 1195.638511815) (100 . "AcDbArc") (50 . 0.978566035) (51 . 1.5329423463))
((0 . "ARC") (100 . "AcDbEntity") (8 . "WINDOWS") (62 . 7) (370 . 13) (100 . "AcDbCircle") (10 14592.7601809955
1112.0537958773 0.0) (40 . 1195.638511815) (100 . "AcDbArc") (50 . 1.5329423463) (51 . 1.599183845))
((0 . "ARC") (100 . "AcDbEntity") (8 . "WINDOWS") (62 . 7) (370 . 13) (100 . "AcDbCircle") (10 14592.7601809955
1112.0537958773 0.0) (40 . 1195.638511815) (100 . "AcDbArc") (50 . 1.599183845) (51 . 2.1630266185))
((0 . "ARC") (100 . "AcDbEntity") (8 . "WINDOWS") (62 . 7) (370 . 13) (100 . "AcDbCircle") (10 1832.5791855204
4745.2394419306 0.0) (40 . 571.5026395173) (100 . "AcDbArc") (50 . 0.55265455) (51 . 1.451835914))
((0 . "ARC") (100 . "AcDbEntity") (8 . "WINDOWS") (62 . 7) (370 . 13) (100 . "AcDbCircle") (10 1832.5791855204
4745.2394419306 0.0) (40 . 571.5026395173) (100 . "AcDbArc") (50 . 1.6897567396) (51 . 2.5889381036))
((0 . "ARC") (100 . "AcDbEntity") (8 . "WINDOWS") (62 . 7) (370 . 13) (100 . "AcDbCircle") (10 1832.5791855204
4651.9829651318 0.0) (40 . 551.6369443705) (100 . "AcDbArc") (50 . 0.709411304) (51 . 2.4321813496))
((0 . "ARC") (100 . "AcDbEntity") (8 . "WINDOWS") (62 . 7) (370 . 13) (100 . "AcDbCircle") (10 1832.5791855204
4594.0654368256 0.0) (40 . 519.0567351201) (100 . "AcDbArc") (50 . 0.799030988) (51 . 1.5053682643))
((0 . "ARC") (100 . "AcDbEntity") (8 . "WINDOWS") (62 . 7) (370 . 13) (100 . "AcDbCircle") (10 1832.5791855204
4594.0654368256 0.0) (40 . 519.0567351201) (100 . "AcDbArc") (50 . 1.5053682643) (51 . 1.6362243893))
((0 . "ARC") (100 . "AcDbEntity") (8 . "WINDOWS") (62 . 7) (370 . 13) (100 . "AcDbCircle") (10 1832.5791855204
4594.0654368256 0.0) (40 . 519.0567351201) (100 . "AcDbArc") (50 . 1.6362243893) (51 . 2.3425616656))
((0 . "ARC") (100 . "AcDbEntity") (8 . "WINDOWS") (62 . 7) (370 . 13) (100 . "AcDbCircle") (10 1832.5791855204
1917.1851432881 0.0) (40 . 571.5026395173) (100 . "AcDbArc") (50 . 0.55265455) (51 . 1.451835914))
((0 . "ARC") (100 . "AcDbEntity") (8 . "WINDOWS") (62 . 7) (370 . 13) (100 . "AcDbCircle") (10 1832.5791855204
1917.1851432881 0.0) (40 . 571.5026395173) (100 . "AcDbArc") (50 . 1.6897567396) (51 . 2.5889381036))
((0 . "ARC") (100 . "AcDbEntity") (8 . "WINDOWS") (62 . 7) (370 . 13) (100 . "AcDbCircle") (10 1832.5791855204
1823.9286664892 0.0) (40 . 551.6369443705) (100 . "AcDbArc") (50 . 0.709411304) (51 . 2.4321813496))
((0 . "ARC") (100 . "AcDbEntity") (8 . "WINDOWS") (62 . 7) (370 . 13) (100 . "AcDbCircle") (10 1832.5791855204
1766.0111381831 0.0) (40 . 519.0567351201) (100 . "AcDbArc") (50 . 0.799030988) (51 . 1.5053682643))
((0 . "ARC") (100 . "AcDbEntity") (8 . "WINDOWS") (62 . 7) (370 . 13) (100 . "AcDbCircle") (10 1832.5791855204
1766.0111381831 0.0) (40 . 519.0567351201) (100 . "AcDbArc") (50 . 1.5053682643) (51 . 1.6362243893))
((0 . "ARC") (100 . "AcDbEntity") (8 . "WINDOWS") (62 . 7) (370 . 13) (100 . "AcDbCircle") (10 1832.5791855204
1766.0111381831 0.0) (40 . 519.0567351201) (100 . "AcDbArc") (50 . 1.6362243893) (51 . 2.3425616656))
((0 . "ARC") (100 . "AcDbEntity") (8 . "WINDOWS") (62 . 7) (370 . 13) (100 . "AcDbCircle") (10 18167.4208144796
4745.2394419306 0.0) (40 . 571.5026395173) (100 . "AcDbArc") (50 . 0.55265455) (51 . 1.451835914))
((0 . "ARC") (100 . "AcDbEntity") (8 . "WINDOWS") (62 . 7) (370 . 13) (100 . "AcDbCircle") (10 18167.4208144796
4745.2394419306 0.0) (40 . 571.5026395173) (100 . "AcDbArc") (50 . 1.6897567396) (51 . 2.5889381036))
((0 . "ARC") (100 . "AcDbEntity") (8 . "WINDOWS") (62 . 7) (370 . 13) (100 . "AcDbCircle") (10 18167.4208144796
4651.9829651318 0.0) (40 . 551.6369443705) (100 . "AcDbArc") (50 . 0.709411304) (51 . 2.4321813496))
((0 . "ARC") (100 . "AcDbEntity") (8 . "WINDOWS") (62 . 7) (370 . 13) (100 . "AcDbCircle") (10 18167.4208144796
4594.0654368256 0.0) (40 . 519.0567351201) (100 . "AcDbArc") (50 . 0.799030988) (51 . 1.5053682643))
((0 . "ARC") (100 . "AcDbEntity") (8 . "WINDOWS") (62 . 7) (370 . 13) (100 . "AcDbCircle") (10 18167.4208144796
4594.0654368256 0.0) (40 . 519.0567351201) (100 . "AcDbArc") (50 . 1.5053682643) (51 . 1.6362243893))
((0 . "ARC") (100 . "AcDbEntity") (8 . "WINDOWS") (62 . 7) (370 . 13) (100 . "AcDbCircle") (10 18167.4208144796
4594.0654368256 0.0) (40 . 519.0567351201) (100 . "AcDbArc") (50 . 1.6362243893) (51 . 2.3425616656))
((0 . "ARC") (100 . "AcDbEntity") (8 . "WINDOWS") (62 . 7) (370 . 13) (100 . "AcDbCircle") (10 18167.4208144796
1917.1851432881 0.0) (40 . 571.5026395173) (100 . "AcDbArc") (50 . 0.55265455) (51 . 1.451835914))
((0 . "ARC") (100 . "AcDbEntity") (8 . "WINDOWS") (62 . 7) (370 . 13) (100 . "AcDbCircle") (10 18167.4208144796
1917.1851432881 0.0) (40 . 571.5026395173) (100 . "AcDbArc") (50 . 1.6897567396) (51 . 2.5889381036))
((0 . "ARC") (100 . "AcDbEntity") (8 . "WINDOWS") (62 . 7) (370 . 13) (100 . "AcDbCircle") (10 18167.4208144796
1823.9286664892 0.0) (40 . 551.6369443705) (100 . "AcDbArc") (50 . 0.709411304) (51 . 2.4321813496))
((0 . "ARC") (100 . "AcDbEntity") (8 . "WINDOWS") (62 . 7) (370 . 13) (100 . "AcDbCircle") (10 18167.4208144796
1766.0111381831 0.0) (40 . 519.0567351201) (100 . "AcDbArc") (50 . 0.799030988) (51 . 1.5053682643))
((0 . "ARC") (100 . "AcDbEntity") (8 . "WINDOWS") (62 . 7) (370 . 13) (100 . "AcDbCircle") (10 18167.4208144796
1766.0111381831 0.0) (40 . 519.0567351201) (100 . "AcDbArc") (50 . 1.5053682643) (51 . 1.6362243893))
((0 . "ARC") (100 . "AcDbEntity") (8 . "WINDOWS") (62 . 7) (370 . 13) (100 . "AcDbCircle") (10 18167.4208144796
1766.0111381831 0.0) (40 . 519.0567351201) (100 . "AcDbArc") (50 . 1.6362243893) (51 . 2.3425616656))
((0 . "ARC") (100 . "AcDbEntity") (8 . "WINDOWS") (62 . 7) (370 . 13) (100 . "AcDbCircle") (10 8755.6561085973
4758.9627567003 0.0) (40 . 648.2770623042) (100 . "AcDbArc") (50 . 0.57795082) (51 . 2.5636418336))
((0 . "ARC") (100 . "AcDbEntity") (8 . "WINDOWS") (62 . 7) (370 . 13) (100 . "AcDbCircle") (10 8755.6561085973
4666.918049271 0.0) (40 . 604.5751633987) (100 . "AcDbArc") (50 . 0.7250884745) (51 . 2.4165041791))
((0 . "ARC") (100 . "AcDbEntity") (8 . "WINDOWS") (62 . 7) (370 . 13) (100 . "AcDbCircle") (10 8755.6561085973
4687.5831780676 0.0) (40 . 527.3489486292) (100 . "AcDbArc") (50 . 0.688437366) (51 . 1.5063985133))
((0 . "ARC") (100 . "AcDbEntity") (8 . "WINDOWS") (62 . 7) (370 . 13) (100 . "AcDbCircle") (10 8755.6561085973
4687.5831780676 0.0) (40 . 527.3489486292) (100 . "AcDbArc") (50 . 1.5063985133) (51 . 1.6351941403))
((0 . "ARC") (100 . "AcDbEntity") (8 . "WINDOWS") (62 . 7) (370 . 13) (100 . "AcDbCircle") (10 8755.6561085973
4687.5831780676 0.0) (40 . 527.3489486292) (100 . "AcDbArc") (50 . 1.6351941403) (51 . 2.4531552876))
((0 . "ARC") (100 . "AcDbEntity") (8 . "WINDOWS") (62 . 7) (370 . 13) (100 . "AcDbCircle") (10 8755.6561085973
1304.6757164404 0.0) (40 . 1093.5143288084) (100 . "AcDbArc") (50 . 0.7610127542) (51 . 1.5138507949))
((0 . "ARC") (100 . "AcDbEntity") (8 . "WINDOWS") (62 . 7) (370 . 13) (100 . "AcDbCircle") (10 8755.6561085973
1304.6757164404 0.0) (40 . 1093.5143288084) (100 . "AcDbArc") (50 . 1.6277418587) (51 . 2.3805798994))
((0 . "ARC") (100 . "AcDbEntity") (8 . "WINDOWS") (62 . 7) (370 . 13) (100 . "AcDbCircle") (10 8755.6561085973
1268.3257918552 0.0) (40 . 1039.3665158371) (100 . "AcDbArc") (50 . 0.8152630109) (51 . 2.3263296427))
((0 . "ARC") (100 . "AcDbEntity") (8 . "WINDOWS") (62 . 7) (370 . 13) (100 . "AcDbCircle") (10 8755.6561085973
1239.2019744961 0.0) (40 . 989.3048128342) (100 . "AcDbArc") (50 . 0.8457078523) (51 . 1.5250423189))
((0 . "ARC") (100 . "AcDbEntity") (8 . "WINDOWS") (62 . 7) (370 . 13) (100 . "AcDbCircle") (10 8755.6561085973
1239.2019744961 0.0) (40 . 989.3048128342) (100 . "AcDbArc") (50 . 1.5250423189) (51 . 1.6165503347))
((0 . "ARC") (100 . "AcDbEntity") (8 . "WINDOWS") (62 . 7) (370 . 13) (100 . "AcDbCircle") (10 8755.6561085973
1239.2019744961 0.0) (40 . 989.3048128342) (100 . "AcDbArc") (50 . 1.6165503347) (51 . 2.2958848013))
((0 . "ARC") (100 . "AcDbEntity") (8 . "WINDOWS") (62 . 7) (370 . 13) (100 . "AcDbCircle") (10 11255.6561085973
4758.9627567003 0.0) (40 . 648.2770623042) (100 . "AcDbArc") (50 . 0.57795082) (51 . 2.5636418336))
((0 . "ARC") (100 . "AcDbEntity") (8 . "WINDOWS") (62 . 7) (370 . 13) (100 . "AcDbCircle") (10 11255.6561085973
4666.918049271 0.0) (40 . 604.5751633987) (100 . "AcDbArc") (50 . 0.7250884745) (51 . 2.4165041791))
((0 . "ARC") (100 . "AcDbEntity") (8 . "WINDOWS") (62 . 7) (370 . 13) (100 . "AcDbCircle") (10 11255.6561085973
4687.5831780676 0.0) (40 . 527.3489486292) (100 . "AcDbArc") (50 . 0.688437366) (51 . 1.5063985133))
((0 . "ARC") (100 . "AcDbEntity") (8 . "WINDOWS") (62 . 7) (370 . 13) (100 . "AcDbCircle") (10 11255.6561085973
4687.5831780676 0.0) (40 . 527.3489486292) (100 . "AcDbArc") (50 . 1.5063985133) (51 . 1.6351941403))
((0 . "ARC") (100 . "AcDbEntity") (8 . "WINDOWS") (62 . 7) (370 . 13) (100 . "AcDbCircle") (10 11255.6561085973
4687.5831780676 0.0) (40 . 527.3489486292) (100 . "AcDbArc") (50 . 1.6351941403) (51 . 2.4531552876))
((0 . "ARC") (100 . "AcDbEntity") (8 . "WINDOWS") (62 . 7) (370 . 13) (100 . "AcDbCircle") (10 11255.6561085973
1304.6757164404 0.0) (40 . 1093.5143288084) (100 . "AcDbArc") (50 . 0.7610127542) (51 . 0.7758969971))
((0 . "ARC") (100 . "AcDbEntity") (8 . "WINDOWS") (62 . 7) (370 . 13) (100 . "AcDbCircle") (10 11255.6561085973
1304.6757164404 0.0) (40 . 1093.5143288084) (100 . "AcDbArc") (50 . 0.7758969971) (51 . 1.5138507949))
((0 . "ARC") (100 . "AcDbEntity") (8 . "WINDOWS") (62 . 7) (370 . 13) (100 . "AcDbCircle") (10 11255.6561085973
1304.6757164404 0.0) (40 . 1093.5143288084) (100 . "AcDbArc") (50 . 1.6277418587) (51 . 2.3805798994))
((0 . "ARC") (100 . "AcDbEntity") (8 . "WINDOWS") (62 . 7) (370 . 13) (100 . "AcDbCircle") (10 11255.6561085973
1268.3257918552 0.0) (40 . 1039.3665158371) (100 . "AcDbArc") (50 . 0.8152630109) (51 . 2.3263296427))
((0 . "ARC") (100 . "AcDbEntity") (8 . "WINDOWS") (62 . 7) (370 . 13) (100 . "AcDbCircle") (10 11255.6561085973
1239.2019744961 0.0) (40 . 989.3048128342) (100 . "AcDbArc") (50 . 0.8457078523) (51 . 1.5250423189))
((0 . "ARC") (100 . "AcDbEntity") (8 . "WINDOWS") (62 . 7) (370 . 13) (100 . "AcDbCircle") (10 11255.6561085973
1239.2019744961 0.0) (40 . 989.3048128342) (100 . "AcDbArc") (50 . 1.5250423189) (51 . 1.6165503347))
((0 . "ARC") (100 . "AcDbEntity") (8 . "WINDOWS") (62 . 7) (370 . 13) (100 . "AcDbCircle") (10 11255.6561085973
1239.2019744961 0.0) (40 . 989.3048128342) (100 . "AcDbArc") (50 . 1.6165503347) (51 . 2.2958848013))
((0 . "LWPOLYLINE") (100 . "AcDbEntity") (8 . "PLANTS") (62 . 94) (370 . 13) (100 . "AcDbPolyline") (90 . 2) (70 . 0)
(43 . 0.0) (10 648.567081448 1014.3287330317) (10 648.567081448 999.2459276018))
((0 . "LWPOLYLINE") (100 . "AcDbEntity") (8 . "PLANTS") (62 . 94) (370 . 13) (100 . "AcDbPolyline") (90 . 3) (70 . 0)
(43 . 0.0) (10 656.1085972851 3857.4660633484) (10 656.1085972851 3834.8416289593) (10 656.1085972851 3812.2171945701))
((0 . "LWPOLYLINE") (100 . "AcDbEntity") (8 . "PLANTS") (62 . 94) (370 . 13) (100 . "AcDbPolyline") (90 . 2) (70 . 0)
(43 . 0.0) (10 1030.9029255312 181.0006372117) (10 892.1738989062 181.0010416337))
((0 . "LWPOLYLINE") (100 . "AcDbEntity") (8 . "PLANTS") (62 . 94) (370 . 13) (100 . "AcDbPolyline") (90 . 2) (70 . 0)
(43 . 0.0) (10 678.7330316742 3774.5093891403) (10 674.6196832598 3775.1950226207))
((0 . "LWPOLYLINE") (100 . "AcDbEntity") (8 . "PLANTS") (62 . 94) (370 . 13) (100 . "AcDbPolyline") (90 . 2) (70 . 0)
(43 . 0.0) (10 957.7676470588 3009.0497737557) (10 892.1749092642 3009.0511978087))
((0 . "LWPOLYLINE") (100 . "AcDbEntity") (8 . "PLANTS") (62 . 94) (370 . 13) (100 . "AcDbPolyline") (90 . 3) (70 . 0)
(43 . 0.0) (10 697.5867647059 3766.9683257919) (10 705.2763574661 3755.8041855204) (10 720.9286789525 3744.3438914027))
((0 . "LWPOLYLINE") (100 . "AcDbEntity") (8 . "PLANTS") (62 . 94) (370 . 13) (100 . "AcDbPolyline") (90 . 3) (70 . 0)
(43 . 0.0) (10 771.367350455 3734.2313741574) (10 773.0015837104 3735.604638009) (10 791.8552036199 3740.5727375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 780.5429864253 931.3716063348 0.0) (10 756.9631387658 947.1743450969 0.0) (10 723.8718875529
920.3298420479 0.0) (10 701.3574660633 946.4564479638 0.0))
((0 . "LWPOLYLINE") (100 . "AcDbEntity") (8 . "PLANTS") (62 . 94) (370 . 13) (100 . "AcDbPolyline") (90 . 2) (70 . 0)
(43 . 0.0) (10 705.1281674208 3834.8416289593) (10 712.6696832579 3838.6127828054))
((0 . "LWPOLYLINE") (100 . "AcDbEntity") (8 . "PLANTS") (62 . 94) (370 . 13) (100 . "AcDbPolyline") (90 . 2) (70 . 0)
(43 . 0.0) (10 712.6696832579 1018.0995475113) (10 708.8989819005 1010.5571266968))
((0 . "LWPOLYLINE") (100 . "AcDbEntity") (8 . "PLANTS") (62 . 94) (370 . 13) (100 . "AcDbPolyline") (90 . 3) (70 . 0)
(43 . 0.0) (10 818.2504524887 595.7777149321) (10 795.6260180995 607.0823529412) (10 795.241941122 607.0815091034))
((0 . "LWPOLYLINE") (100 . "AcDbEntity") (8 . "PLANTS") (62 . 94) (370 . 13) (100 . "AcDbPolyline") (90 . 3) (70 . 0)
(43 . 0.0) (10 799.3966063348 1044.4937782805) (10 776.7787330317 1039.6676470588) (10 765.4599547511 1025.6419683258))
((0 . "LWPOLYLINE") (100 . "AcDbEntity") (8 . "PLANTS") (62 . 94) (370 . 13) (100 . "AcDbPolyline") (90 . 3) (70 . 0)
(43 . 0.0) (10 773.0015837104 3861.2372171946) (10 784.313800905 3871.3515837104) (10 803.1674208145 3876.3193438914))
((0 . "LWPOLYLINE") (100 . "AcDbEntity") (8 . "PLANTS") (62 . 94) (370 . 13) (100 . "AcDbPolyline") (90 . 3) (70 . 0)
(43 . 0.0) (10 789.0579835697 3512.6070537491) (10 799.3900452489 3520.6721719457) (10 806.9382352941 3521.8700226244))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.8532633946) (40
. 1) (40 . 1) (40 . 1) (40 . 1) (10 844.6454751131 3612.3677601811 0.0) (10 827.9771915999 3615.2653087083 0.0) (10
800.8681815847 3614.1428667971 0.0) (10 782.7598403497 3613.3519364468 0.0) (10 781.4669295128 3607.706092073 0.0))
((0 . "LWPOLYLINE") (100 . "AcDbEntity") (8 . "PLANTS") (62 . 94) (370 . 13) (100 . "AcDbPolyline") (90 . 2) (70 . 0)
(43 . 0.0) (10 783.1007728046 3587.2376663896) (10 784.313800905 3585.9728506787))
((0 . "LWPOLYLINE") (100 . "AcDbEntity") (8 . "PLANTS") (62 . 94) (370 . 13) (100 . "AcDbPolyline") (90 . 2) (70 . 0)
(43 . 0.0) (10 803.1674208145 3740.5727375566) (10 791.8552036199 3740.5727375566))
((0 . "LWPOLYLINE") (100 . "AcDbEntity") (8 . "PLANTS") (62 . 94) (370 . 13) (100 . "AcDbPolyline") (90 . 3) (70 . 0)
(43 . 0.0) (10 803.1674208145 3766.9683257919) (10 796.8235294118 3759.420361991) (10 791.8552036199 3740.5727375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 822.021040724 3453.996719457 0.0) (10 799.0286287659 3438.4340766516 0.0) (10 823.0690758101
3403.7217030329 0.0) (10 798.8669638028 3391.6137742005 0.0))
((0 . "LWPOLYLINE") (100 . "AcDbEntity") (8 . "PLANTS") (62 . 94) (370 . 13) (100 . "AcDbPolyline") (90 . 2) (70 . 0)
(43 . 0.0) (10 799.3966063348 3695.3238687783) (10 810.7088235294 3714.1783936652))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 871.0407239819 1044.4937782805 0.0) (10 848.7544919471 1038.6390172465 0.0) (10 820.8583977185
1029.6446555443 0.0) (10 799.3966063348 1044.4937782805 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 852.1871040724 1082.2030542986 0.0) (10 831.4595032383 1076.3362009703 0.0) (10 806.2386952115
1067.1873570562 0.0) (10 799.3966063348 1044.4937782805 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 871.0407239819 3849.925 0.0) (10 857.5267401917 3878.6926282448 0.0) (10 821.6417702025 3855.7622553287
0.0) (10 803.1674208145 3876.3193438914 0.0))
((0 . "LWPOLYLINE") (100 . "AcDbEntity") (8 . "PLANTS") (62 . 94) (370 . 13) (100 . "AcDbPolyline") (90 . 3) (70 . 0)
(43 . 0.0) (10 803.1674208145 3876.3193438914) (10 810.8570135747 3890.346040724) (10 825.7918552036 3895.1738687783))
((0 . "LWPOLYLINE") (100 . "AcDbEntity") (8 . "PLANTS") (62 . 94) (370 . 13) (100 . "AcDbPolyline") (90 . 3) (70 . 0)
(43 . 0.0) (10 803.1674208145 3766.9683257919) (10 806.9382352941 3763.1971719457) (10 818.2504524887 3763.1971719457))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5814925152) (40
. 1) (40 . 1) (40 . 1) (40 . 1) (10 803.1674208145 3766.9683257918 0.0) (10 806.9498660273 3789.9888453092 0.0) (10
827.266433778 3820.7263006001 0.0) (10 859.429795572 3840.0476755005 0.0) (10 871.0407239819 3849.9249999999 0.0))
((0 . "LWPOLYLINE") (100 . "AcDbEntity") (8 . "PLANTS") (62 . 94) (370 . 13) (100 . "AcDbPolyline") (90 . 3) (70 . 0)
(43 . 0.0) (10 810.7088235294 3725.4906108597) (10 804.365158371 3729.4154977376) (10 803.1674208145 3740.5727375566))
((0 . "LWPOLYLINE") (100 . "AcDbEntity") (8 . "PLANTS") (62 . 94) (370 . 13) (100 . "AcDbPolyline") (90 . 2) (70 . 0)
(43 . 0.0) (10 818.2504524887 3763.1971719457) (10 803.1674208145 3740.5727375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 806.9382352941 3521.8700226244 0.0) (10 826.9703602982 3503.3855315148 0.0) (10 855.9557033493
3518.5445373413 0.0) (10 855.9576923077 3540.7239819005 0.0))
((0 . "LWPOLYLINE") (100 . "AcDbEntity") (8 . "PLANTS") (62 . 94) (370 . 13) (100 . "AcDbPolyline") (90 . 3) (70 . 0)
(43 . 0.0) (10 806.9382352941 3521.8700226244) (10 819.3001131222 3551.8884615385) (10 840.8748868778 3563.3484162896))
((0 . "LWPOLYLINE") (100 . "AcDbEntity") (8 . "PLANTS") (62 . 94) (370 . 13) (100 . "AcDbPolyline") (90 . 2) (70 . 0)
(43 . 0.0) (10 810.7088235294 3725.4906108597) (10 810.7088235294 3714.1783936652))
((0 . "LWPOLYLINE") (100 . "AcDbEntity") (8 . "PLANTS") (62 . 94) (370 . 13) (100 . "AcDbPolyline") (90 . 3) (70 . 0)
(43 . 0.0) (10 840.8748868778 3748.1150452489) (10 833.1851809955 3734.2358597285) (10 810.7088235294 3725.4906108597))
((0 . "LWPOLYLINE") (100 . "AcDbEntity") (8 . "PLANTS") (62 . 94) (370 . 13) (100 . "AcDbPolyline") (90 . 3) (70 . 0)
(43 . 0.0) (10 874.8115384615 3710.407239819) (10 822.0211538462 3706.7910633484) (10 810.7088235294 3714.1783936652))
((0 . "LWPOLYLINE") (100 . "AcDbEntity") (8 . "PLANTS") (62 . 94) (370 . 13) (100 . "AcDbPolyline") (90 . 2) (70 . 0)
(43 . 0.0) (10 837.1040723982 3978.1292986425) (10 814.479638009 3974.3593891403))
((0 . "LWPOLYLINE") (100 . "AcDbEntity") (8 . "PLANTS") (62 . 94) (370 . 13) (100 . "AcDbPolyline") (90 . 2) (70 . 0)
(43 . 0.0) (10 814.479638009 3646.3050904977) (10 833.3332579186 3668.9295248869))
((0 . "LWPOLYLINE") (100 . "AcDbEntity") (8 . "PLANTS") (62 . 94) (370 . 13) (100 . "AcDbPolyline") (90 . 2) (70 . 0)
(43 . 0.0) (10 822.021040724 3453.996719457) (10 814.479638009 3472.850678733))
((0 . "LWPOLYLINE") (100 . "AcDbEntity") (8 . "PLANTS") (62 . 94) (370 . 13) (100 . "AcDbPolyline") (90 . 2) (70 . 0)
(43 . 0.0) (10 822.021040724 3310.7091628959) (10 815.3415150675 3324.0681140149))
((0 . "LWPOLYLINE") (100 . "AcDbEntity") (8 . "PLANTS") (62 . 94) (370 . 13) (100 . "AcDbPolyline") (90 . 2) (70 . 0)
(43 . 0.0) (10 822.021040724 3310.7091628959) (10 819.6774266909 3306.2908763594))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 878.5821266968 3367.2702488688 0.0) (10 854.1933664698 3364.5174594805 0.0) (10 822.2825922511
3351.3721406638 0.0) (10 814.6542173727 3326.8860345635 0.0))
((0 . "LWPOLYLINE") (100 . "AcDbEntity") (8 . "PLANTS") (62 . 94) (370 . 13) (100 . "AcDbPolyline") (90 . 2) (70 . 0)
(43 . 0.0) (10 818.2504524887 3763.1971719457) (10 829.5626696833 3763.1971719457))
((0 . "LWPOLYLINE") (100 . "AcDbEntity") (8 . "PLANTS") (62 . 94) (370 . 13) (100 . "AcDbPolyline") (90 . 3) (70 . 0)
(43 . 0.0) (10 822.021040724 3453.996719457) (10 859.7285067873 3465.161199095) (10 878.5821266968 3461.5384615385))
((0 . "LWPOLYLINE") (100 . "AcDbEntity") (8 . "PLANTS") (62 . 94) (370 . 13) (100 . "AcDbPolyline") (90 . 2) (70 . 0)
(43 . 0.0) (10 848.4162895928 3314.4796380091) (10 822.021040724 3310.7091628959))
((0 . "LWPOLYLINE") (100 . "AcDbEntity") (8 . "PLANTS") (62 . 94) (370 . 13) (100 . "AcDbPolyline") (90 . 3) (70 . 0)
(43 . 0.0) (10 832.3907239819 3901.7718325792) (10 829.5626696833 3895.1738687783) (10 825.7918552036 3895.1738687783))
((0 . "LWPOLYLINE") (100 . "AcDbEntity") (8 . "PLANTS") (62 . 94) (370 . 13) (100 . "AcDbPolyline") (90 . 3) (70 . 0)
(43 . 0.0) (10 832.3907239819 3901.7718325792) (10 825.7918552036 3898.9437782805) (10 825.7918552036 3895.1738687783))
((0 . "LWPOLYLINE") (100 . "AcDbEntity") (8 . "PLANTS") (62 . 94) (370 . 13) (100 . "AcDbPolyline") (90 . 2) (70 . 0)
(43 . 0.0) (10 840.8748868778 3748.1150452489) (10 829.5626696833 3763.1971719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 886.1237556561 3831.0704751131 0.0) (10 867.5108477417 3810.7839369513 0.0) (10 834.0672121546
3794.086123215 0.0) (10 829.5626696833 3763.1971719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 832.3907239819 3901.7718325792 0.0) (10 859.3751165229 3888.7107189018 0.0) (10 883.1739685683
3930.6802085514 0.0) (10 912.5187782805 3906.4860859729 0.0))
((0 . "LWPOLYLINE") (100 . "AcDbEntity") (8 . "PLANTS") (62 . 94) (370 . 13) (100 . "AcDbPolyline") (90 . 3) (70 . 0)
(43 . 0.0) (10 832.3907239819 3901.7718325792) (10 830.8779411765 3913.7005656109) (10 863.499321267 3947.963800905))
((0 . "SPLINE") (100 . "AcDbEntity") (8 . "PLANTS") (62 . 94) (370 . 13) (100 . "AcDbSpline") (70 . 3) (71 . 3) (72 .
10) (73 . 6) (74 . 0) (42 . 0.0000001) (43 . 0.0000001) (40 . -1) (40 . -0.6783666266) (40 . -0.3215814263) (40 . 0.0)
(40 . 0.3216333734) (40 . 0.6784185737) (40 . 1) (40 . 1.3216333734) (40 . 1.6784185737) (40 . 2) (10 836.8355749343
3903.5369662139 0.0) (10 830.9187789093 3900.2995800788 0.0) (10 834.1552265313 3906.2182154343 0.0) (10 836.8355749343
3903.5369662139 0.0) (10 830.9187789093 3900.2995800788 0.0) (10 834.1552265313 3906.2182154343 0.0))
((0 . "LWPOLYLINE") (100 . "AcDbEntity") (8 . "PLANTS") (62 . 94) (370 . 13) (100 . "AcDbPolyline") (90 . 2) (70 . 0)
(43 . 0.0) (10 837.1040723982 3978.1292986425) (10 863.499321267 3963.0471719457))
((0 . "LWPOLYLINE") (100 . "AcDbEntity") (8 . "PLANTS") (62 . 94) (370 . 13) (100 . "AcDbPolyline") (90 . 3) (70 . 0)
(43 . 0.0) (10 871.0407239819 3989.4415158371) (10 855.9576923077 3988.3919683258) (10 837.1040723982 3978.1292986425))
((0 . "LWPOLYLINE") (100 . "AcDbEntity") (8 . "PLANTS") (62 . 94) (370 . 13) (100 . "AcDbPolyline") (90 . 2) (70 . 0)
(43 . 0.0) (10 840.8748868778 3748.1150452489) (10 867.2699095023 3751.8849547511))
((0 . "LWPOLYLINE") (100 . "AcDbEntity") (8 . "PLANTS") (62 . 94) (370 . 13) (100 . "AcDbPolyline") (90 . 2) (70 . 0)
(43 . 0.0) (10 840.8748868778 3563.3484162896) (10 855.9576923077 3540.7239819005))
((0 . "LWPOLYLINE") (100 . "AcDbEntity") (8 . "PLANTS") (62 . 94) (370 . 13) (100 . "AcDbPolyline") (90 . 2) (70 . 0)
(43 . 0.0) (10 840.8748868778 3563.3484162896) (10 844.6454751131 3612.367760181))
((0 . "LWPOLYLINE") (100 . "AcDbEntity") (8 . "PLANTS") (62 . 94) (370 . 13) (100 . "AcDbPolyline") (90 . 3) (70 . 0)
(43 . 0.0) (10 840.8748868778 916.2895927602) (10 855.9576923077 930.1744343891) (10 874.8115384615 935.1442307692))
((0 . "LWPOLYLINE") (100 . "AcDbEntity") (8 . "PLANTS") (62 . 94) (370 . 13) (100 . "AcDbPolyline") (90 . 2) (70 . 0)
(43 . 0.0) (10 844.6454751131 3612.367760181) (10 859.7285067873 3612.367760181))
((0 . "LWPOLYLINE") (100 . "AcDbEntity") (8 . "PLANTS") (62 . 94) (370 . 13) (100 . "AcDbPolyline") (90 . 2) (70 . 0)
(43 . 0.0) (10 848.4162895928 3333.3335972851) (10 848.4162895928 3314.4796380091))
((0 . "LWPOLYLINE") (100 . "AcDbEntity") (8 . "PLANTS") (62 . 94) (370 . 13) (100 . "AcDbPolyline") (90 . 2) (70 . 0)
(43 . 0.0) (10 874.8115384615 3310.7091628959) (10 848.4162895928 3314.4796380091))
((0 . "LWPOLYLINE") (100 . "AcDbEntity") (8 . "PLANTS") (62 . 94) (370 . 13) (100 . "AcDbPolyline") (90 . 3) (70 . 0)
(43 . 0.0) (10 874.8115384615 3310.7091628959) (10 869.8364253394 3273.0081447964) (10 848.4162895928 3257.9185520362))
((0 . "LWPOLYLINE") (100 . "AcDbEntity") (8 . "PLANTS") (62 . 94) (370 . 13) (100 . "AcDbPolyline") (90 . 2) (70 . 0)
(43 . 0.0) (10 852.1871040724 1082.2030542986) (10 871.0407239819 1082.2030542986))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 852.1871040724 1082.2030542986 0.0) (10 845.6510768989 1094.9069879498 0.0) (10 855.1837649294
1117.6039345914 0.0) (10 871.0407239819 1116.1397058824 0.0))
((0 . "LWPOLYLINE") (100 . "AcDbEntity") (8 . "PLANTS") (62 . 94) (370 . 13) (100 . "AcDbPolyline") (90 . 3) (70 . 0)
(43 . 0.0) (10 889.8943438914 3544.4944570136) (10 882.3463800905 3540.871719457) (10 855.9576923077 3540.7239819005))
((0 . "LWPOLYLINE") (100 . "AcDbEntity") (8 . "PLANTS") (62 . 94) (370 . 13) (100 . "AcDbPolyline") (90 . 2) (70 . 0)
(43 . 0.0) (10 889.8943438914 3608.5972850679) (10 859.7285067873 3612.367760181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 874.8115384615 3710.407239819 0.0) (10 890.524785001 3675.8304777611 0.0) (10 856.3456935312
3646.9840393691 0.0) (10 859.7285067873 3612.367760181 0.0))
((0 . "LWPOLYLINE") (100 . "AcDbEntity") (8 . "PLANTS") (62 . 94) (370 . 13) (100 . "AcDbPolyline") (90 . 2) (70 . 0)
(43 . 0.0) (10 859.7285067873 1180.2403846154) (10 871.0407239819 1180.2403846154))
((0 . "LWPOLYLINE") (100 . "AcDbEntity") (8 . "PLANTS") (62 . 94) (370 . 13) (100 . "AcDbPolyline") (90 . 2) (70 . 0)
(43 . 0.0) (10 863.499321267 3947.963800905) (10 863.499321267 3963.0471719457))
((0 . "LWPOLYLINE") (100 . "AcDbEntity") (8 . "PLANTS") (62 . 94) (370 . 13) (100 . "AcDbPolyline") (90 . 2) (70 . 0)
(43 . 0.0) (10 871.0407239819 3974.3593891403) (10 863.499321267 3963.0471719457))
((0 . "LWPOLYLINE") (100 . "AcDbEntity") (8 . "PLANTS") (62 . 94) (370 . 13) (100 . "AcDbPolyline") (90 . 3) (70 . 0)
(43 . 0.0) (10 912.5187782805 3932.8804298643) (10 893.665158371 3942.995361991) (10 863.499321267 3947.963800905))
((0 . "LWPOLYLINE") (100 . "AcDbEntity") (8 . "PLANTS") (62 . 94) (370 . 13) (100 . "AcDbPolyline") (90 . 2) (70 . 0)
(43 . 0.0) (10 863.499321267 972.850678733) (10 908.7481900452 1040.7239819005))
((0 . "LWPOLYLINE") (100 . "AcDbEntity") (8 . "PLANTS") (62 . 94) (370 . 13) (100 . "AcDbPolyline") (90 . 3) (70 . 0)
(43 . 0.0) (10 863.499321267 893.665158371) (10 901.206561086 922.6271493213) (10 953.9970588235 927.6018099548))
((0 . "LWPOLYLINE") (100 . "AcDbEntity") (8 . "PLANTS") (62 . 94) (370 . 13) (100 . "AcDbPolyline") (90 . 3) (70 . 0)
(43 . 0.0) (10 886.1237556561 3733.0316742081) (10 878.5755656109 3744.3376696833) (10 867.2699095023 3751.8849547511))
((0 . "LWPOLYLINE") (100 . "AcDbEntity") (8 . "PLANTS") (62 . 94) (370 . 13) (100 . "AcDbPolyline") (90 . 3) (70 . 0)
(43 . 0.0) (10 867.2699095023 3751.8849547511) (10 883.5570135747 3812.2109728507) (10 893.665158371 3819.7582579186))
((0 . "LWPOLYLINE") (100 . "AcDbEntity") (8 . "PLANTS") (62 . 94) (370 . 13) (100 . "AcDbPolyline") (90 . 3) (70 . 0)
(43 . 0.0) (10 908.7481900452 886.1227375566) (10 888.8382352941 852.1860859729) (10 867.2699095023 829.5616515837))
((0 . "LWPOLYLINE") (100 . "AcDbEntity") (8 . "PLANTS") (62 . 94) (370 . 13) (100 . "AcDbPolyline") (90 . 2) (70 . 0)
(43 . 0.0) (10 871.0407239819 3989.4415158371) (10 871.0407239819 3974.3593891403))
((0 . "LWPOLYLINE") (100 . "AcDbEntity") (8 . "PLANTS") (62 . 94) (370 . 13) (100 . "AcDbPolyline") (90 . 2) (70 . 0)
(43 . 0.0) (10 871.0407239819 3989.4415158371) (10 874.8115384615 4000.7537330317))
((0 . "LWPOLYLINE") (100 . "AcDbEntity") (8 . "PLANTS") (62 . 94) (370 . 13) (100 . "AcDbPolyline") (90 . 2) (70 . 0)
(43 . 0.0) (10 889.8943438914 3978.1292986425) (10 871.0407239819 3974.3593891403))
((0 . "LWPOLYLINE") (100 . "AcDbEntity") (8 . "PLANTS") (62 . 94) (370 . 13) (100 . "AcDbPolyline") (90 . 2) (70 . 0)
(43 . 0.0) (10 871.0407239819 3849.925) (10 886.1237556561 3849.925))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 946.4554298643 1116.1397058824 0.0) (10 948.3836905948 1172.1066870998 0.0) (10 873.0266544775
1128.7450318933 0.0) (10 871.0407239819 1180.2403846154 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4279084357)
(40 . 0.5823704577) (40 . 1) (40 . 1) (40 . 1) (40 . 1) (10 984.1628959276 1161.3885746606 0.0) (10 964.6807993646
1161.2565513829 0.0) (10 950.2454948132 1186.5208313252 0.0) (10 909.9577914258 1185.0919980359 0.0) (10 883.7681749736
1192.4957399691 0.0) (10 871.0407239819 1180.2403846154 0.0))
((0 . "LWPOLYLINE") (100 . "AcDbEntity") (8 . "PLANTS") (62 . 94) (370 . 13) (100 . "AcDbPolyline") (90 . 2) (70 . 0)
(43 . 0.0) (10 871.0407239819 1044.4937782805) (10 871.0407239819 1082.2030542986))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 871.0407239819 1082.2030542986 0.0) (10 909.3202356169 1069.9579804698 0.0) (10 907.9256761334
1129.2279568957 0.0) (10 946.4554298643 1116.1397058824 0.0))
((0 . "LWPOLYLINE") (100 . "AcDbEntity") (8 . "PLANTS") (62 . 94) (370 . 13) (100 . "AcDbPolyline") (90 . 3) (70 . 0)
(43 . 0.0) (10 871.0407239819 1044.4937782805) (10 901.2 1044.346719457) (10 908.7481900452 1040.7239819005))
((0 . "LWPOLYLINE") (100 . "AcDbEntity") (8 . "PLANTS") (62 . 94) (370 . 13) (100 . "AcDbPolyline") (90 . 2) (70 . 0)
(43 . 0.0) (10 882.3529411765 731.524321267) (10 871.0407239819 720.2121040724))
((0 . "LWPOLYLINE") (100 . "AcDbEntity") (8 . "PLANTS") (62 . 94) (370 . 13) (100 . "AcDbPolyline") (90 . 2) (70 . 0)
(43 . 0.0) (10 920.0604072398 4046.00260181) (10 874.8115384615 4049.7737556561))
((0 . "LWPOLYLINE") (100 . "AcDbEntity") (8 . "PLANTS") (62 . 94) (370 . 13) (100 . "AcDbPolyline") (90 . 2) (70 . 0)
(43 . 0.0) (10 874.8115384615 3710.407239819) (10 886.1237556561 3733.0316742081))
((0 . "LWPOLYLINE") (100 . "AcDbEntity") (8 . "PLANTS") (62 . 94) (370 . 13) (100 . "AcDbPolyline") (90 . 2) (70 . 0)
(43 . 0.0) (10 874.8115384615 3310.7091628959) (10 893.665158371 3318.2501131222))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 927.6018099548 607.0899321267 0.0) (10 897.9189732313 593.3366589758 0.0) (10 881.5415145489
562.1005689894 0.0) (10 874.8115384615 531.6742081448 0.0))
((0 . "LWPOLYLINE") (100 . "AcDbEntity") (8 . "PLANTS") (62 . 94) (370 . 13) (100 . "AcDbPolyline") (90 . 2) (70 . 0)
(43 . 0.0) (10 878.5821266968 3461.5384615385) (10 878.5821266968 3435.1435520362))
((0 . "LWPOLYLINE") (100 . "AcDbEntity") (8 . "PLANTS") (62 . 94) (370 . 13) (100 . "AcDbPolyline") (90 . 2) (70 . 0)
(43 . 0.0) (10 908.7481900452 3480.3924208145) (10 878.5821266968 3461.5384615385))
((0 . "LWPOLYLINE") (100 . "AcDbEntity") (8 . "PLANTS") (62 . 94) (370 . 13) (100 . "AcDbPolyline") (90 . 2) (70 . 0)
(43 . 0.0) (10 893.665158371 3427.6018099548) (10 878.5821266968 3435.1435520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 878.5821266969 3435.1435520362 0.0) (10 851.4001104006 3426.9345355568 0.0) (10 850.0637835371
3392.4883840451 0.0) (10 878.5821266968 3382.3529411765 0.0))
((0 . "LWPOLYLINE") (100 . "AcDbEntity") (8 . "PLANTS") (62 . 94) (370 . 13) (100 . "AcDbPolyline") (90 . 2) (70 . 0)
(43 . 0.0) (10 878.5821266968 3367.2702488688) (10 878.5821266968 3382.3529411765))
((0 . "LWPOLYLINE") (100 . "AcDbEntity") (8 . "PLANTS") (62 . 94) (370 . 13) (100 . "AcDbPolyline") (90 . 2) (70 . 0)
(43 . 0.0) (10 916.2895927602 3386.1234162896) (10 878.5821266968 3382.3529411765))
((0 . "LWPOLYLINE") (100 . "AcDbEntity") (8 . "PLANTS") (62 . 94) (370 . 13) (100 . "AcDbPolyline") (90 . 2) (70 . 0)
(43 . 0.0) (10 893.665158371 3352.1867647059) (10 878.5821266968 3367.2702488688))
((0 . "LWPOLYLINE") (100 . "AcDbEntity") (8 . "PLANTS") (62 . 94) (370 . 13) (100 . "AcDbPolyline") (90 . 2) (70 . 0)
(43 . 0.0) (10 882.3529411765 731.524321267) (10 893.665158371 723.9819004525))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 882.3529411765 731.524321267 0.0) (10 888.6143069428 762.6672703818 0.0) (10 923.251589979
775.7154839916 0.0) (10 950.2262443439 780.5429864253 0.0))
((0 . "LWPOLYLINE") (100 . "AcDbEntity") (8 . "PLANTS") (62 . 94) (370 . 13) (100 . "AcDbPolyline") (90 . 3) (70 . 0)
(43 . 0.0) (10 882.3529411765 629.7143665158) (10 901.206561086 651.140158371) (10 942.684841629 659.8783936652))
((0 . "LWPOLYLINE") (100 . "AcDbEntity") (8 . "PLANTS") (62 . 94) (370 . 13) (100 . "AcDbPolyline") (90 . 2) (70 . 0)
(43 . 0.0) (10 886.1237556561 3849.925) (10 886.1237556561 3831.0704751131))
((0 . "LWPOLYLINE") (100 . "AcDbEntity") (8 . "PLANTS") (62 . 94) (370 . 13) (100 . "AcDbPolyline") (90 . 3) (70 . 0)
(43 . 0.0) (10 920.0604072398 3861.2372171946) (10 901.206561086 3860.1805429864) (10 886.1237556561 3849.925))
((0 . "LWPOLYLINE") (100 . "AcDbEntity") (8 . "PLANTS") (62 . 94) (370 . 13) (100 . "AcDbPolyline") (90 . 3) (70 . 0)
(43 . 0.0) (10 886.1237556561 3831.0704751131) (10 893.665158371 3827.3005656109) (10 893.665158371 3819.7582579186))
((0 . "LWPOLYLINE") (100 . "AcDbEntity") (8 . "PLANTS") (62 . 94) (370 . 13) (100 . "AcDbPolyline") (90 . 2) (70 . 0)
(43 . 0.0) (10 886.1237556561 3733.0316742081) (10 904.9773755656 3733.0316742081))
((0 . "LWPOLYLINE") (100 . "AcDbEntity") (8 . "PLANTS") (62 . 94) (370 . 13) (100 . "AcDbPolyline") (90 . 3) (70 . 0)
(43 . 0.0) (10 889.8943438914 3544.4944570136) (10 893.665158371 3563.3484162896) (10 889.8943438914 3608.5972850679))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3210409497)
(40 . 0.8148442996) (40 . 1) (40 . 1) (40 . 1) (40 . 1) (10 889.8943438915 3608.5972850678 0.0) (10 901.3202493218
3617.4972124986 0.0) (10 900.6915711635 3653.2014700798 0.0) (10 917.0055426121 3698.6691052647 0.0) (10 909.7658367345
3725.973055677 0.0) (10 904.9773755657 3733.0316742081 0.0))
((0 . "LWPOLYLINE") (100 . "AcDbEntity") (8 . "PLANTS") (62 . 94) (370 . 13) (100 . "AcDbPolyline") (90 . 2) (70 . 0)
(43 . 0.0) (10 889.8943438914 3544.4944570136) (10 908.7481900452 3480.3924208145))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 961.5384615385 3993.2126696833 0.0) (10 959.7583043326 4022.5148526113 0.0) (10 908.0959415239
4021.8598891775 0.0) (10 893.665158371 4012.0659502262 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 893.665158371 3819.7582579186 0.0) (10 898.5176092384 3804.5876565791 0.0) (10 920.216021962
3811.995421127 0.0) (10 923.8309954751 3797.1338235294 0.0))
((0 . "LWPOLYLINE") (100 . "AcDbEntity") (8 . "PLANTS") (62 . 94) (370 . 13) (100 . "AcDbPolyline") (90 . 2) (70 . 0)
(43 . 0.0) (10 893.665158371 3352.1867647059) (10 893.665158371 3318.2501131222))
((0 . "LWPOLYLINE") (100 . "AcDbEntity") (8 . "PLANTS") (62 . 94) (370 . 13) (100 . "AcDbPolyline") (90 . 2) (70 . 0)
(43 . 0.0) (10 893.665158371 3352.1867647059) (10 916.2895927602 3378.5824660633))
((0 . "LWPOLYLINE") (100 . "AcDbEntity") (8 . "PLANTS") (62 . 94) (370 . 13) (100 . "AcDbPolyline") (90 . 2) (70 . 0)
(43 . 0.0) (10 927.6018099548 3306.9378959276) (10 893.665158371 3318.2501131222))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 897.4359728507 946.4564479638 0.0) (10 926.0961359796 961.7827514779 0.0) (10 918.8029885113
1002.7499716214 0.0) (10 950.2262443439 1014.3297511312 0.0))
((0 . "LWPOLYLINE") (100 . "AcDbEntity") (8 . "PLANTS") (62 . 94) (370 . 13) (100 . "AcDbPolyline") (90 . 2) (70 . 0)
(43 . 0.0) (10 897.4359728507 806.9372171946) (10 908.7481900452 810.709841629))
((0 . "LWPOLYLINE") (100 . "AcDbEntity") (8 . "PLANTS") (62 . 94) (370 . 13) (100 . "AcDbPolyline") (90 . 3) (70 . 0)
(43 . 0.0) (10 901.206561086 3205.1279411765) (10 927.7497737557 3239.0645927602) (10 942.684841629 3250.3768099548))
((0 . "LWPOLYLINE") (100 . "AcDbEntity") (8 . "PLANTS") (62 . 94) (370 . 13) (100 . "AcDbPolyline") (90 . 3) (70 . 0)
(43 . 0.0) (10 904.9773755656 3733.0316742081) (10 915.2332579186 3751.8849547511) (10 923.8309954751 3797.1338235294))
((0 . "LWPOLYLINE") (100 . "AcDbEntity") (8 . "PLANTS") (62 . 94) (370 . 13) (100 . "AcDbPolyline") (90 . 2) (70 . 0)
(43 . 0.0) (10 904.9773755656 3114.6302036199) (10 916.2895927602 3122.1719457014))
((0 . "LWPOLYLINE") (100 . "AcDbEntity") (8 . "PLANTS") (62 . 94) (370 . 13) (100 . "AcDbPolyline") (90 . 2) (70 . 0)
(43 . 0.0) (10 908.7481900452 3480.3924208145) (10 931.3726244344 3480.3924208145))
((0 . "LWPOLYLINE") (100 . "AcDbEntity") (8 . "PLANTS") (62 . 94) (370 . 13) (100 . "AcDbPolyline") (90 . 2) (70 . 0)
(43 . 0.0) (10 942.684841629 1044.4937782805) (10 908.7481900452 1040.7239819005))
((0 . "LWPOLYLINE") (100 . "AcDbEntity") (8 . "PLANTS") (62 . 94) (370 . 13) (100 . "AcDbPolyline") (90 . 2) (70 . 0)
(43 . 0.0) (10 935.1432126697 720.2121040724) (10 908.7481900452 720.2121040724))
((0 . "LWPOLYLINE") (100 . "AcDbEntity") (8 . "PLANTS") (62 . 94) (370 . 13) (100 . "AcDbPolyline") (90 . 2) (70 . 0)
(43 . 0.0) (10 912.5187782805 3932.8804298643) (10 912.5187782805 3906.4860859729))
((0 . "LWPOLYLINE") (100 . "AcDbEntity") (8 . "PLANTS") (62 . 94) (370 . 13) (100 . "AcDbPolyline") (90 . 3) (70 . 0)
(43 . 0.0) (10 912.5187782805 3932.8804298643) (10 927.6018099548 3947.5951357466) (10 961.5384615385 3951.7349547511))
((0 . "LWPOLYLINE") (100 . "AcDbEntity") (8 . "PLANTS") (62 . 94) (370 . 13) (100 . "AcDbPolyline") (90 . 2) (70 . 0)
(43 . 0.0) (10 923.8309954751 3895.1738687783) (10 912.5187782805 3906.4860859729))
((0 . "LWPOLYLINE") (100 . "AcDbEntity") (8 . "PLANTS") (62 . 94) (370 . 13) (100 . "AcDbPolyline") (90 . 2) (70 . 0)
(43 . 0.0) (10 923.8309954751 456.2584841629) (10 912.5187782805 429.8642533937))
((0 . "LWPOLYLINE") (100 . "AcDbEntity") (8 . "PLANTS") (62 . 94) (370 . 13) (100 . "AcDbPolyline") (90 . 3) (70 . 0)
(43 . 0.0) (10 950.2262443439 3981.9004524887) (10 935.1432126697 3981.7523755656) (10 916.2895927602 3974.3593891403))
((0 . "LWPOLYLINE") (100 . "AcDbEntity") (8 . "PLANTS") (62 . 94) (370 . 13) (100 . "AcDbPolyline") (90 . 2) (70 . 0)
(43 . 0.0) (10 916.2895927602 3386.1234162896) (10 916.2895927602 3378.5824660633))
((0 . "LWPOLYLINE") (100 . "AcDbEntity") (8 . "PLANTS") (62 . 94) (370 . 13) (100 . "AcDbPolyline") (90 . 3) (70 . 0)
(43 . 0.0) (10 916.2895927602 3386.1234162896) (10 917.4938914027 3401.2069004525) (10 942.684841629 3427.6018099548))
((0 . "LWPOLYLINE") (100 . "AcDbEntity") (8 . "PLANTS") (62 . 94) (370 . 13) (100 . "AcDbPolyline") (90 . 2) (70 . 0)
(43 . 0.0) (10 916.2895927602 3378.5824660633) (10 938.9140271493 3374.811199095))
((0 . "LWPOLYLINE") (100 . "AcDbEntity") (8 . "PLANTS") (62 . 94) (370 . 13) (100 . "AcDbPolyline") (90 . 2) (70 . 0)
(43 . 0.0) (10 923.8309954751 3122.1719457014) (10 916.2895927602 3122.1719457014))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 942.684841629 3178.7330316742 0.0) (10 917.5614343948 3174.3952785786 0.0) (10 913.8013459076
3142.3534041133 0.0) (10 916.2895927602 3122.1719457014 0.0))
((0 . "LWPOLYLINE") (100 . "AcDbEntity") (8 . "PLANTS") (62 . 94) (370 . 13) (100 . "AcDbPolyline") (90 . 2) (70 . 0)
(43 . 0.0) (10 920.0604072398 3861.2372171946) (10 953.9970588235 3834.8416289593))
((0 . "LWPOLYLINE") (100 . "AcDbEntity") (8 . "PLANTS") (62 . 94) (370 . 13) (100 . "AcDbPolyline") (90 . 3) (70 . 0)
(43 . 0.0) (10 920.0604072398 3861.2372171946) (10 920.2083710407 3887.6253393665) (10 923.8309954751 3895.1738687783))
((0 . "LWPOLYLINE") (100 . "AcDbEntity") (8 . "PLANTS") (62 . 94) (370 . 13) (100 . "AcDbPolyline") (90 . 3) (70 . 0)
(43 . 0.0) (10 923.8309954751 3895.1738687783) (10 961.5317873303 3914.1817873303) (10 969.0798642534 3929.110520362))
((0 . "LWPOLYLINE") (100 . "AcDbEntity") (8 . "PLANTS") (62 . 94) (370 . 13) (100 . "AcDbPolyline") (90 . 2) (70 . 0)
(43 . 0.0) (10 938.9140271493 3797.1338235294) (10 923.8309954751 3797.1338235294))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 927.6018099548 3306.9378959276 0.0) (10 921.4389997569 3284.6691377228 0.0) (10 951.3363947423
3274.2268475772 0.0) (10 942.684841629 3250.3768099548 0.0))
((0 . "LWPOLYLINE") (100 . "AcDbEntity") (8 . "PLANTS") (62 . 94) (370 . 13) (100 . "AcDbPolyline") (90 . 2) (70 . 0)
(43 . 0.0) (10 946.4554298643 3322.0213800905) (10 927.6018099548 3306.9378959276))
((0 . "LWPOLYLINE") (100 . "AcDbEntity") (8 . "PLANTS") (62 . 94) (370 . 13) (100 . "AcDbPolyline") (90 . 2) (70 . 0)
(43 . 0.0) (10 927.6018099548 607.0899321267) (10 953.9970588235 599.5475113122))
((0 . "LWPOLYLINE") (100 . "AcDbEntity") (8 . "PLANTS") (62 . 94) (370 . 13) (100 . "AcDbPolyline") (90 . 3) (70 . 0)
(43 . 0.0) (10 927.6018099548 607.0899321267) (10 934.2481900452 633.4841628959) (10 946.4554298643 644.7963800905))
((0 . "LWPOLYLINE") (100 . "AcDbEntity") (8 . "PLANTS") (62 . 94) (370 . 13) (100 . "AcDbPolyline") (90 . 2) (70 . 0)
(43 . 0.0) (10 942.684841629 3427.6018099548) (10 931.3726244344 3480.3924208145))
((0 . "LWPOLYLINE") (100 . "AcDbEntity") (8 . "PLANTS") (62 . 94) (370 . 13) (100 . "AcDbPolyline") (90 . 2) (70 . 0)
(43 . 0.0) (10 957.7676470588 3514.3290723982) (10 931.3726244344 3480.3924208145))
((0 . "LWPOLYLINE") (100 . "AcDbEntity") (8 . "PLANTS") (62 . 94) (370 . 13) (100 . "AcDbPolyline") (90 . 2) (70 . 0)
(43 . 0.0) (10 950.2262443439 833.3342760181) (10 931.3726244344 829.5616515837))
((0 . "LWPOLYLINE") (100 . "AcDbEntity") (8 . "PLANTS") (62 . 94) (370 . 13) (100 . "AcDbPolyline") (90 . 3) (70 . 0)
(43 . 0.0) (10 1014.3287330317 1289.592760181) (10 991.7042986425 1290.7907239819) (10 985.1031957771 1293.7967499712))
((0 . "LWPOLYLINE") (100 . "AcDbEntity") (8 . "PLANTS") (62 . 94) (370 . 13) (100 . "AcDbPolyline") (90 . 3) (70 . 0)
(43 . 0.0) (10 935.1432126697 720.2121040724) (10 935.1432126697 716.439479638) (10 946.4554298643 708.8998868778))
((0 . "LWPOLYLINE") (100 . "AcDbEntity") (8 . "PLANTS") (62 . 94) (370 . 13) (100 . "AcDbPolyline") (90 . 3) (70 . 0)
(43 . 0.0) (10 953.9970588235 761.6883484163) (10 943.7345022624 750.3761312217) (10 935.1432126697 720.2121040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 957.7676470588 3680.2417420814 0.0) (10 943.6488462377 3718.7440383004 0.0) (10 976.6138217996
3769.0746172539 0.0) (10 938.9140271493 3797.1338235294 0.0))
((0 . "LWPOLYLINE") (100 . "AcDbEntity") (8 . "PLANTS") (62 . 94) (370 . 13) (100 . "AcDbPolyline") (90 . 3) (70 . 0)
(43 . 0.0) (10 953.9970588235 3815.9883484163) (10 947.4985294118 3812.0625565611) (10 938.9140271493 3797.1338235294))
((0 . "LWPOLYLINE") (100 . "AcDbEntity") (8 . "PLANTS") (62 . 94) (370 . 13) (100 . "AcDbPolyline") (90 . 2) (70 . 0)
(43 . 0.0) (10 946.4554298643 3322.0213800905) (10 938.9140271493 3374.811199095))
((0 . "LWPOLYLINE") (100 . "AcDbEntity") (8 . "PLANTS") (62 . 94) (370 . 13) (100 . "AcDbPolyline") (90 . 2) (70 . 0)
(43 . 0.0) (10 961.5384615385 3382.3529411765) (10 938.9140271493 3374.811199095))
((0 . "LWPOLYLINE") (100 . "AcDbEntity") (8 . "PLANTS") (62 . 94) (370 . 13) (100 . "AcDbPolyline") (90 . 3) (70 . 0)
(43 . 0.0) (10 957.7676470588 1217.9496606335) (10 936.4957013575 1236.8014705882) (10 938.9140271493 1248.1136877828))
((0 . "LWPOLYLINE") (100 . "AcDbEntity") (8 . "PLANTS") (62 . 94) (370 . 13) (100 . "AcDbPolyline") (90 . 3) (70 . 0)
(43 . 0.0) (10 938.9140271493 501.5073529412) (10 946.4621040724 511.62239819) (10 961.5384615385 516.5921945701))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 961.5384615385 3382.3529411765 0.0) (10 958.9651820684 3394.1788924386 0.0) (10 961.0526367325
3423.0639721186 0.0) (10 942.684841629 3427.6018099548 0.0))
((0 . "LWPOLYLINE") (100 . "AcDbEntity") (8 . "PLANTS") (62 . 94) (370 . 13) (100 . "AcDbPolyline") (90 . 3) (70 . 0)
(43 . 0.0) (10 942.684841629 3250.3768099548) (10 953.8423076923 3239.0645927602) (10 953.9970588235 3201.3574660633))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 942.684841629 3178.7330316742 0.0) (10 973.1259781882 3149.1599230067 0.0) (10 960.0660658304
3098.2891937286 0.0) (10 950.2262443439 3061.8403846154 0.0))
((0 . "LWPOLYLINE") (100 . "AcDbEntity") (8 . "PLANTS") (62 . 94) (370 . 13) (100 . "AcDbPolyline") (90 . 3) (70 . 0)
(43 . 0.0) (10 942.684841629 3178.7330316742) (10 945.560520362 3193.8095022624) (10 953.9970588235 3201.3574660633))
((0 . "LWPOLYLINE") (100 . "AcDbEntity") (8 . "PLANTS") (62 . 94) (370 . 13) (100 . "AcDbPolyline") (90 . 2) (70 . 0)
(43 . 0.0) (10 942.684841629 1044.4937782805) (10 950.2262443439 1033.181561086))
((0 . "LWPOLYLINE") (100 . "AcDbEntity") (8 . "PLANTS") (62 . 94) (370 . 13) (100 . "AcDbPolyline") (90 . 3) (70 . 0)
(43 . 0.0) (10 942.684841629 1044.4937782805) (10 968.0236425339 1093.5152714932) (10 969.0798642534 1112.367081448))
((0 . "LWPOLYLINE") (100 . "AcDbEntity") (8 . "PLANTS") (62 . 94) (370 . 13) (100 . "AcDbPolyline") (90 . 2) (70 . 0)
(43 . 0.0) (10 946.4554298643 656.1085972851) (10 942.684841629 659.8783936652))
((0 . "LWPOLYLINE") (100 . "AcDbEntity") (8 . "PLANTS") (62 . 94) (370 . 13) (100 . "AcDbPolyline") (90 . 3) (70 . 0)
(43 . 0.0) (10 946.4554298643 656.1085972851) (10 942.684841629 656.1085972851) (10 942.684841629 659.8783936652))
((0 . "LWPOLYLINE") (100 . "AcDbEntity") (8 . "PLANTS") (62 . 94) (370 . 13) (100 . "AcDbPolyline") (90 . 2) (70 . 0)
(43 . 0.0) (10 942.684841629 659.8783936652) (10 946.4554298643 708.8998868778))
((0 . "LWPOLYLINE") (100 . "AcDbEntity") (8 . "PLANTS") (62 . 94) (370 . 13) (100 . "AcDbPolyline") (90 . 2) (70 . 0)
(43 . 0.0) (10 953.9970588235 358.2211538462) (10 942.684841629 358.2211538462))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4582495878) (40
. 1) (40 . 1) (40 . 1) (40 . 1) (10 946.4554298643 3322.0213800906 0.0) (10 971.2382188098 3311.1363462334 0.0) (10
992.6054542195 3252.778762674 0.0) (10 1046.7229176283 3218.4985490507 0.0) (10 1036.9531674209 3182.5035067874 0.0))
((0 . "LWPOLYLINE") (100 . "AcDbEntity") (8 . "PLANTS") (62 . 94) (370 . 13) (100 . "AcDbPolyline") (90 . 2) (70 . 0)
(43 . 0.0) (10 969.0798642534 1112.367081448) (10 946.4554298643 1116.1397058824))
((0 . "LWPOLYLINE") (100 . "AcDbEntity") (8 . "PLANTS") (62 . 94) (370 . 13) (100 . "AcDbPolyline") (90 . 2) (70 . 0)
(43 . 0.0) (10 984.1628959276 708.8998868778) (10 946.4554298643 708.8998868778))
((0 . "LWPOLYLINE") (100 . "AcDbEntity") (8 . "PLANTS") (62 . 94) (370 . 13) (100 . "AcDbPolyline") (90 . 3) (70 . 0)
(43 . 0.0) (10 946.4554298643 656.1085972851) (10 976.6213800905 654.9037330317) (10 1003.0165158371 625.9417420814))
((0 . "LWPOLYLINE") (100 . "AcDbEntity") (8 . "PLANTS") (62 . 94) (370 . 13) (100 . "AcDbPolyline") (90 . 2) (70 . 0)
(43 . 0.0) (10 946.4554298643 656.1085972851) (10 946.4554298643 644.7963800905))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 953.9970588235 599.5475113122 0.0) (10 960.8492830862 614.0292923666 0.0) (10 957.3792794022
633.2065825953 0.0) (10 946.4554298643 644.7963800905 0.0))
((0 . "LWPOLYLINE") (100 . "AcDbEntity") (8 . "PLANTS") (62 . 94) (370 . 13) (100 . "AcDbPolyline") (90 . 2) (70 . 0)
(43 . 0.0) (10 950.2262443439 3981.9004524887) (10 961.5384615385 3951.7349547511))
((0 . "LWPOLYLINE") (100 . "AcDbEntity") (8 . "PLANTS") (62 . 94) (370 . 13) (100 . "AcDbPolyline") (90 . 3) (70 . 0)
(43 . 0.0) (10 950.2262443439 3981.9004524887) (10 957.7676470588 3993.2126696833) (10 961.5384615385 3993.2126696833))
((0 . "LWPOLYLINE") (100 . "AcDbEntity") (8 . "PLANTS") (62 . 94) (370 . 13) (100 . "AcDbPolyline") (90 . 2) (70 . 0)
(43 . 0.0) (10 950.2262443439 3061.8403846154) (10 972.850678733 3054.2986425339))
((0 . "LWPOLYLINE") (100 . "AcDbEntity") (8 . "PLANTS") (62 . 94) (370 . 13) (100 . "AcDbPolyline") (90 . 2) (70 . 0)
(43 . 0.0) (10 957.7676470588 3009.0497737557) (10 950.2262443439 3061.8403846154))
((0 . "LWPOLYLINE") (100 . "AcDbEntity") (8 . "PLANTS") (62 . 94) (370 . 13) (100 . "AcDbPolyline") (90 . 2) (70 . 0)
(43 . 0.0) (10 950.2262443439 1033.181561086) (10 950.2262443439 1014.3297511312))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1036.9531674208 1070.8908371041 0.0) (10 1002.2553709904 1070.9981703199 0.0) (10 983.7696344795
1036.9018292614 0.0) (10 950.2262443439 1033.181561086 0.0))
((0 . "LWPOLYLINE") (100 . "AcDbEntity") (8 . "PLANTS") (62 . 94) (370 . 13) (100 . "AcDbPolyline") (90 . 3) (70 . 0)
(43 . 0.0) (10 965.3092760181 972.850678733) (10 960.3342760181 1003.0175339367) (10 950.2262443439 1014.3297511312))
((0 . "LWPOLYLINE") (100 . "AcDbEntity") (8 . "PLANTS") (62 . 94) (370 . 13) (100 . "AcDbPolyline") (90 . 2) (70 . 0)
(43 . 0.0) (10 950.2262443439 833.3342760181) (10 950.2262443439 780.5429864253))
((0 . "LWPOLYLINE") (100 . "AcDbEntity") (8 . "PLANTS") (62 . 94) (370 . 13) (100 . "AcDbPolyline") (90 . 2) (70 . 0)
(43 . 0.0) (10 950.2262443439 833.3342760181) (10 953.9970588235 927.6018099548))
((0 . "LWPOLYLINE") (100 . "AcDbEntity") (8 . "PLANTS") (62 . 94) (370 . 13) (100 . "AcDbPolyline") (90 . 2) (70 . 0)
(43 . 0.0) (10 953.9970588235 761.6883484163) (10 950.2262443439 780.5429864253))
((0 . "LWPOLYLINE") (100 . "AcDbEntity") (8 . "PLANTS") (62 . 94) (370 . 13) (100 . "AcDbPolyline") (90 . 2) (70 . 0)
(43 . 0.0) (10 953.9970588235 3834.8416289593) (10 953.9970588235 3815.9883484163))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 953.9970588235 3834.8416289593 0.0) (10 972.2362159378 3855.5860277308 0.0) (10 998.2695875717
3895.0362529777 0.0) (10 1033.1825791855 3891.4027149321 0.0))
((0 . "LWPOLYLINE") (100 . "AcDbEntity") (8 . "PLANTS") (62 . 94) (370 . 13) (100 . "AcDbPolyline") (90 . 3) (70 . 0)
(43 . 0.0) (10 953.9970588235 3815.9883484163) (10 961.5451357466 3812.3652714932) (10 991.7042986425 3812.2171945701))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1010.5581447964 3144.7963800905 0.0) (10 982.2955930321 3155.2237550857 0.0) (10 984.5322686575
3194.499302486 0.0) (10 953.9970588235 3201.3574660633 0.0))
((0 . "LWPOLYLINE") (100 . "AcDbEntity") (8 . "PLANTS") (62 . 94) (370 . 13) (100 . "AcDbPolyline") (90 . 3) (70 . 0)
(43 . 0.0) (10 965.3092760181 972.850678733) (10 964.2530542986 957.7686651584) (10 953.9970588235 927.6018099548))
((0 . "LWPOLYLINE") (100 . "AcDbEntity") (8 . "PLANTS") (62 . 94) (370 . 13) (100 . "AcDbPolyline") (90 . 3) (70 . 0)
(43 . 0.0) (10 953.9970588235 761.6883484163) (10 971.7943438914 746.6001131222) (10 984.1628959276 708.8998868778))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 953.9970588235 599.5475113122 0.0) (10 973.8488245155 593.6201390621 0.0) (10 954.8300747945
566.0085412075 0.0) (10 972.850678733 561.8410633484 0.0))
((0 . "LWPOLYLINE") (100 . "AcDbEntity") (8 . "PLANTS") (62 . 94) (370 . 13) (100 . "AcDbPolyline") (90 . 3) (70 . 0)
(43 . 0.0) (10 953.9970588235 316.742081448) (10 965.1545248869 335.596719457) (10 953.9970588235 358.2211538462))
((0 . "LWPOLYLINE") (100 . "AcDbEntity") (8 . "PLANTS") (62 . 94) (370 . 13) (100 . "AcDbPolyline") (90 . 3) (70 . 0)
(43 . 0.0) (10 953.9970588235 358.2211538462) (10 961.6865384615 368.3347285068) (10 976.6214932127 369.5333710407))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 957.7676470588 3680.2417420814 0.0) (10 1004.7632409317 3678.8741674404 0.0) (10 956.1555724455
3600.2621804048 0.0) (10 1021.870361991 3612.367760181 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 957.7676470586 3680.2417420815 0.0) (10 951.8052404569 3627.9220870659 0.0) (10 937.804885465
3566.0031217662 0.0) (10 957.7676470588 3514.3290723982 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 984.1628959275 3578.4311085973 0.0) (10 977.4291572521 3557.2003951367 0.0) (10 998.4106595409
3512.2025837778 0.0) (10 957.7676470588 3514.3290723982 0.0))
((0 . "LWPOLYLINE") (100 . "AcDbEntity") (8 . "PLANTS") (62 . 94) (370 . 13) (100 . "AcDbPolyline") (90 . 3) (70 . 0)
(43 . 0.0) (10 957.7676470588 3009.0497737557) (10 957.9222850679 2986.4253393665) (10 965.3092760181 2975.1131221719))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 957.7676470588 3009.0497737557 0.0) (10 984.3897986008 2994.3160752349 0.0) (10 1006.5002714818
3016.9269262659 0.0) (10 1031.8421614383 3012.9058030736 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 957.7676470588 1217.9496606335 0.0) (10 974.0861832258 1220.7225630061 0.0) (10 981.0058749202
1261.6058157368 0.0) (10 957.7676470588 1259.4259049774 0.0))
((0 . "LWPOLYLINE") (100 . "AcDbEntity") (8 . "PLANTS") (62 . 94) (370 . 13) (100 . "AcDbPolyline") (90 . 3) (70 . 0)
(43 . 0.0) (10 957.7676470588 1217.9496606335) (10 961.6930995475 1207.8408371041) (10 980.392081448 1199.0950226244))
((0 . "LWPOLYLINE") (100 . "AcDbEntity") (8 . "PLANTS") (62 . 94) (370 . 13) (100 . "AcDbPolyline") (90 . 3) (70 . 0)
(43 . 0.0) (10 961.5384615385 3993.2126696833) (10 987.9337104072 3985.8194570136) (10 1018.0995475113 3985.6716063348))
((0 . "LWPOLYLINE") (100 . "AcDbEntity") (8 . "PLANTS") (62 . 94) (370 . 13) (100 . "AcDbPolyline") (90 . 2) (70 . 0)
(43 . 0.0) (10 969.0798642534 3929.110520362) (10 961.5384615385 3951.7349547511))
((0 . "LWPOLYLINE") (100 . "AcDbEntity") (8 . "PLANTS") (62 . 94) (370 . 13) (100 . "AcDbPolyline") (90 . 3) (70 . 0)
(43 . 0.0) (10 961.5384615385 3382.3529411765) (10 972.8507918552 3381.1487556561) (10 999.2459276018 3355.9580316742))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 972.850678733 411.0096153846 0.0) (10 932.5653200216 445.3130386342 0.0) (10 988.1421332896
482.4422322875 0.0) (10 961.5384615385 516.5921945701 0.0))
((0 . "LWPOLYLINE") (100 . "AcDbEntity") (8 . "PLANTS") (62 . 94) (370 . 13) (100 . "AcDbPolyline") (90 . 3) (70 . 0)
(43 . 0.0) (10 961.5384615385 516.5921945701) (10 970.2711538462 546.6029411765) (10 976.6214932127 550.5288461538))
((0 . "LWPOLYLINE") (100 . "AcDbEntity") (8 . "PLANTS") (62 . 94) (370 . 13) (100 . "AcDbPolyline") (90 . 2) (70 . 0)
(43 . 0.0) (10 965.3092760181 972.850678733) (10 995.4751131222 976.6204751131))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1036.9531674208 3932.8804298643 0.0) (10 1019.0684938948 3915.4305792778 0.0) (10 990.7382085122
3923.8472460636 0.0) (10 969.0798642534 3929.110520362 0.0))
((0 . "LWPOLYLINE") (100 . "AcDbEntity") (8 . "PLANTS") (62 . 94) (370 . 13) (100 . "AcDbPolyline") (90 . 3) (70 . 0)
(43 . 0.0) (10 969.0798642534 1112.367081448) (10 987.9337104072 1112.5154977376) (10 1021.870361991 1123.6792986425))
((0 . "LWPOLYLINE") (100 . "AcDbEntity") (8 . "PLANTS") (62 . 94) (370 . 13) (100 . "AcDbPolyline") (90 . 2) (70 . 0)
(43 . 0.0) (10 972.850678733 561.8410633484) (10 976.6214932127 558.068438914))
((0 . "LWPOLYLINE") (100 . "AcDbEntity") (8 . "PLANTS") (62 . 94) (370 . 13) (100 . "AcDbPolyline") (90 . 3) (70 . 0)
(43 . 0.0) (10 972.850678733 561.8410633484) (10 972.850678733 558.068438914) (10 976.6214932127 558.068438914))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 972.850678733 561.8410633484 0.0) (10 974.1090873891 571.8943252378 0.0) (10 986.6764332262
559.3268000963 0.0) (10 976.6214932127 558.068438914 0.0))
((0 . "LWPOLYLINE") (100 . "AcDbEntity") (8 . "PLANTS") (62 . 94) (370 . 13) (100 . "AcDbPolyline") (90 . 2) (70 . 0)
(43 . 0.0) (10 976.6214932127 550.5288461538) (10 976.6214932127 558.068438914))
((0 . "LWPOLYLINE") (100 . "AcDbEntity") (8 . "PLANTS") (62 . 94) (370 . 13) (100 . "AcDbPolyline") (90 . 3) (70 . 0)
(43 . 0.0) (10 976.6214932127 550.5288461538) (10 994.4253393665 542.8317873303) (10 1021.870361991 505.2799773756))
((0 . "LWPOLYLINE") (100 . "AcDbEntity") (8 . "PLANTS") (62 . 94) (370 . 13) (100 . "AcDbPolyline") (90 . 2) (70 . 0)
(43 . 0.0) (10 1018.0995475113 701.3574660633) (10 984.1628959276 708.8998868778))
((0 . "LWPOLYLINE") (100 . "AcDbEntity") (8 . "PLANTS") (62 . 94) (370 . 13) (100 . "AcDbPolyline") (90 . 3) (70 . 0)
(43 . 0.0) (10 1018.0995475113 3058.0691176471) (10 1020.8139140271 3073.15260181) (10 987.9337104072 3125.9424208145))
((0 . "LWPOLYLINE") (100 . "AcDbEntity") (8 . "PLANTS") (62 . 94) (370 . 13) (100 . "AcDbPolyline") (90 . 3) (70 . 0)
(43 . 0.0) (10 1003.0165158371 3770.739479638) (10 996.5313348416 3782.0516968326) (10 991.7042986425 3812.2171945701))
((0 . "LWPOLYLINE") (100 . "AcDbEntity") (8 . "PLANTS") (62 . 94) (370 . 13) (100 . "AcDbPolyline") (90 . 3) (70 . 0)
(43 . 0.0) (10 1018.0995475113 3842.3826923077) (10 1000.4435520362 3827.1521493213) (10 991.7042986425
3812.2171945701))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 991.7042986425 237.556561086 0.0) (10 1004.6985262519 254.8796149019 0.0) (10 1032.0417683646
232.7745150177 0.0) (10 1021.8703619909 214.9321266968 0.0))
((0 . "LWPOLYLINE") (100 . "AcDbEntity") (8 . "PLANTS") (62 . 94) (370 . 13) (100 . "AcDbPolyline") (90 . 2) (70 . 0)
(43 . 0.0) (10 995.4751131222 976.6204751131) (10 1014.3287330317 957.7686651584))
((0 . "LWPOLYLINE") (100 . "AcDbEntity") (8 . "PLANTS") (62 . 94) (370 . 13) (100 . "AcDbPolyline") (90 . 2) (70 . 0)
(43 . 0.0) (10 995.4751131222 976.6204751131) (10 1006.7873303167 999.2449095023))
((0 . "LWPOLYLINE") (100 . "AcDbEntity") (8 . "PLANTS") (62 . 94) (370 . 13) (100 . "AcDbPolyline") (90 . 2) (70 . 0)
(43 . 0.0) (10 1010.5581447964 3355.9580316742) (10 999.2459276018 3355.9580316742))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1033.1825791855 3310.7091628959 0.0) (10 1010.6710004055 3307.4775862063 0.0) (10 996.1380602455
3337.2832095456 0.0) (10 999.2459276018 3355.9580316742 0.0))
((0 . "LWPOLYLINE") (100 . "AcDbEntity") (8 . "PLANTS") (62 . 94) (370 . 13) (100 . "AcDbPolyline") (90 . 2) (70 . 0)
(43 . 0.0) (10 1003.0165158371 3770.739479638) (10 1021.870361991 3770.739479638))
((0 . "LWPOLYLINE") (100 . "AcDbEntity") (8 . "PLANTS") (62 . 94) (370 . 13) (100 . "AcDbPolyline") (90 . 3) (70 . 0)
(43 . 0.0) (10 1003.0165158371 3770.739479638) (10 995.6363122172 3740.5734162896) (10 1006.7873303167 3729.260520362))
((0 . "LWPOLYLINE") (100 . "AcDbEntity") (8 . "PLANTS") (62 . 94) (370 . 13) (100 . "AcDbPolyline") (90 . 2) (70 . 0)
(43 . 0.0) (10 1021.870361991 3435.1435520362) (10 1003.0165158371 3435.1435520362))
((0 . "LWPOLYLINE") (100 . "AcDbEntity") (8 . "PLANTS") (62 . 94) (370 . 13) (100 . "AcDbPolyline") (90 . 2) (70 . 0)
(43 . 0.0) (10 1003.0165158371 625.9417420814) (10 1018.0995475113 625.9417420814))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1021.870361991 592.0050904977 0.0) (10 1003.9053887519 589.5816191765 0.0) (10 992.8846010417
613.3533391536 0.0) (10 1003.0165158371 625.9417420814 0.0))
((0 . "LWPOLYLINE") (100 . "AcDbEntity") (8 . "PLANTS") (62 . 94) (370 . 13) (100 . "AcDbPolyline") (90 . 3) (70 . 0)
(43 . 0.0) (10 1006.7873303167 3729.260520362) (10 1011.7557692308 3699.1012443439) (10 1018.0995475113 3691.553959276))
((0 . "LWPOLYLINE") (100 . "AcDbEntity") (8 . "PLANTS") (62 . 94) (370 . 13) (100 . "AcDbPolyline") (90 . 2) (70 . 0)
(43 . 0.0) (10 1029.4117647059 3744.3438914027) (10 1006.7873303167 3729.260520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1033.1825791855 3310.7091628959 0.0) (10 1044.4931553547 3327.2295336623 0.0) (10 1036.9868006514
3357.3706730556 0.0) (10 1010.5581447964 3355.9580316742 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1021.870361991 3435.1435520362 0.0) (10 1079.9864167204 3387.598556236 0.0) (10 1009.5986056844
3391.8632606544 0.0) (10 1010.5581447964 3355.9580316742 0.0))
((0 . "LWPOLYLINE") (100 . "AcDbEntity") (8 . "PLANTS") (62 . 94) (370 . 13) (100 . "AcDbPolyline") (90 . 3) (70 . 0)
(43 . 0.0) (10 1014.3287330317 1289.592760181) (10 1014.4768099548 1263.1985294118) (10 1029.4117647059
1225.4892533937))
((0 . "LWPOLYLINE") (100 . "AcDbEntity") (8 . "PLANTS") (62 . 94) (370 . 13) (100 . "AcDbPolyline") (90 . 3) (70 . 0)
(43 . 0.0) (10 1014.3287330317 1289.592760181) (10 1018.0995475113 1297.1351809955) (10 1021.870361991 1297.1351809955))
((0 . "LWPOLYLINE") (100 . "AcDbEntity") (8 . "PLANTS") (62 . 94) (370 . 13) (100 . "AcDbPolyline") (90 . 3) (70 . 0)
(43 . 0.0) (10 1023.7556561086 903.0910633484) (10 1010.7062217195 923.8320135747) (10 1014.3287330317 957.7686651584))
((0 . "LWPOLYLINE") (100 . "AcDbEntity") (8 . "PLANTS") (62 . 94) (370 . 13) (100 . "AcDbPolyline") (90 . 2) (70 . 0)
(43 . 0.0) (10 1048.2653846154 967.1945701357) (10 1014.3287330317 957.7686651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1014.3287330317 282.8054298643 0.0) (10 1032.2718485558 338.6592638596 0.0) (10 980.7473619816
402.6412674272 0.0) (10 1018.0995475113 452.4886877828 0.0))
((0 . "LWPOLYLINE") (100 . "AcDbEntity") (8 . "PLANTS") (62 . 94) (370 . 13) (100 . "AcDbPolyline") (90 . 2) (70 . 0)
(43 . 0.0) (10 1025.6409502262 3993.2126696833) (10 1018.0995475113 3993.2126696833))
((0 . "LWPOLYLINE") (100 . "AcDbEntity") (8 . "PLANTS") (62 . 94) (370 . 13) (100 . "AcDbPolyline") (90 . 2) (70 . 0)
(43 . 0.0) (10 1018.0995475113 3985.6716063348) (10 1018.0995475113 3993.2126696833))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1023.7556561086 4070.5132352941 0.0) (10 996.6981999308 4068.484574041 0.0) (10 988.5392952876
4103.4870694891 0.0) (10 964.5490775853 4106.0401884663 0.0))
((0 . "LWPOLYLINE") (100 . "AcDbEntity") (8 . "PLANTS") (62 . 94) (370 . 13) (100 . "AcDbPolyline") (90 . 3) (70 . 0)
(43 . 0.0) (10 938.7001211885 4091.8209235579) (10 946.6036199095 4072.3981900452) (10 1018.0995475113 3993.2126696833))
((0 . "LWPOLYLINE") (100 . "AcDbEntity") (8 . "PLANTS") (62 . 94) (370 . 13) (100 . "AcDbPolyline") (90 . 2) (70 . 0)
(43 . 0.0) (10 1036.9531674208 3932.8804298643) (10 1018.0995475113 3985.6716063348))
((0 . "LWPOLYLINE") (100 . "AcDbEntity") (8 . "PLANTS") (62 . 94) (370 . 13) (100 . "AcDbPolyline") (90 . 2) (70 . 0)
(43 . 0.0) (10 1025.6409502262 3627.4505656109) (10 1018.0995475113 3691.553959276))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1018.0995475113 3691.553959276 0.0) (10 1047.3957145599 3711.9066101913 0.0) (10 1071.9602646222
3681.1414951855 0.0) (10 1101.0558823529 3687.7828054299 0.0))
((0 . "LWPOLYLINE") (100 . "AcDbEntity") (8 . "PLANTS") (62 . 94) (370 . 13) (100 . "AcDbPolyline") (90 . 2) (70 . 0)
(43 . 0.0) (10 1025.6409502262 690.0452488688) (10 1018.0995475113 701.3574660633))
((0 . "LWPOLYLINE") (100 . "AcDbEntity") (8 . "PLANTS") (62 . 94) (370 . 13) (100 . "AcDbPolyline") (90 . 2) (70 . 0)
(43 . 0.0) (10 1018.0995475113 701.3574660633) (10 1021.870361991 742.8365384615))
((0 . "LWPOLYLINE") (100 . "AcDbEntity") (8 . "PLANTS") (62 . 94) (370 . 13) (100 . "AcDbPolyline") (90 . 3) (70 . 0)
(43 . 0.0) (10 1021.870361991 592.0050904977) (10 1035.5283936652 610.8597285068) (10 1018.0995475113 625.9417420814))
((0 . "LWPOLYLINE") (100 . "AcDbEntity") (8 . "PLANTS") (62 . 94) (370 . 13) (100 . "AcDbPolyline") (90 . 3) (70 . 0)
(43 . 0.0) (10 1025.6409502262 690.0452488688) (10 1025.4929864253 652.338800905) (10 1018.0995475113 625.9417420814))
((0 . "LWPOLYLINE") (100 . "AcDbEntity") (8 . "PLANTS") (62 . 94) (370 . 13) (100 . "AcDbPolyline") (90 . 3) (70 . 0)
(43 . 0.0) (10 1044.4947963801 426.0944570136) (10 1029.263800905 447.6617647059) (10 1018.0995475113 452.4886877828))
((0 . "LWPOLYLINE") (100 . "AcDbEntity") (8 . "PLANTS") (62 . 94) (370 . 13) (100 . "AcDbPolyline") (90 . 3) (70 . 0)
(43 . 0.0) (10 1018.0995475113 452.4886877828) (10 1011.7624434389 475.1131221719) (10 1021.870361991 505.2799773756))
((0 . "LWPOLYLINE") (100 . "AcDbEntity") (8 . "PLANTS") (62 . 94) (370 . 13) (100 . "AcDbPolyline") (90 . 2) (70 . 0)
(43 . 0.0) (10 1029.4117647059 3744.3438914027) (10 1021.870361991 3770.739479638))
((0 . "LWPOLYLINE") (100 . "AcDbEntity") (8 . "PLANTS") (62 . 94) (370 . 13) (100 . "AcDbPolyline") (90 . 3) (70 . 0)
(43 . 0.0) (10 1055.8070135747 3785.8216063348) (10 1036.9531674208 3781.0012443439) (10 1021.870361991 3770.739479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1021.870361991 3612.367760181 0.0) (10 971.0853255586 3546.5608723881 0.0) (10 1066.4431993654
3574.3795060333 0.0) (10 1044.4947963801 3529.4117647059 0.0))
((0 . "LWPOLYLINE") (100 . "AcDbEntity") (8 . "PLANTS") (62 . 94) (370 . 13) (100 . "AcDbPolyline") (90 . 2) (70 . 0)
(43 . 0.0) (10 1021.870361991 3612.367760181) (10 1025.6409502262 3627.4505656109))
((0 . "LWPOLYLINE") (100 . "AcDbEntity") (8 . "PLANTS") (62 . 94) (370 . 13) (100 . "AcDbPolyline") (90 . 2) (70 . 0)
(43 . 0.0) (10 1021.870361991 3435.1435520362) (10 1021.870361991 3450.2262443439))
((0 . "LWPOLYLINE") (100 . "AcDbEntity") (8 . "PLANTS") (62 . 94) (370 . 13) (100 . "AcDbPolyline") (90 . 3) (70 . 0)
(43 . 0.0) (10 1021.870361991 3450.2262443439) (10 1018.2477375566 3465.3089366516) (10 1025.6409502262
3480.3924208145))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1021.8703619909 3450.2262443439 0.0) (10 1047.1801049973 3439.9213194306 0.0) (10 1052.214810709
3481.9468606606 0.0) (10 1025.6409502262 3480.3924208145 0.0))
((0 . "LWPOLYLINE") (100 . "AcDbEntity") (8 . "PLANTS") (62 . 94) (370 . 13) (100 . "AcDbPolyline") (90 . 2) (70 . 0)
(43 . 0.0) (10 1021.870361991 1297.1351809955) (10 1055.8070135747 1297.1351809955))
((0 . "LWPOLYLINE") (100 . "AcDbEntity") (8 . "PLANTS") (62 . 94) (370 . 13) (100 . "AcDbPolyline") (90 . 3) (70 . 0)
(43 . 0.0) (10 1021.8702488688 1322.0790985033) (10 1021.8702488688 1312.2171945701) (10 1021.870361991
1297.1351809955))
((0 . "LWPOLYLINE") (100 . "AcDbEntity") (8 . "PLANTS") (62 . 94) (370 . 13) (100 . "AcDbPolyline") (90 . 2) (70 . 0)
(43 . 0.0) (10 1074.6606334842 1108.5972850679) (10 1021.870361991 1123.6792986425))
((0 . "LWPOLYLINE") (100 . "AcDbEntity") (8 . "PLANTS") (62 . 94) (370 . 13) (100 . "AcDbPolyline") (90 . 3) (70 . 0)
(43 . 0.0) (10 1025.6409502262 1172.7007918552) (10 1022.0183257919 1161.3885746606) (10 1021.870361991
1123.6792986425))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.602942319) (40 .
1) (40 . 1) (40 . 1) (40 . 1) (10 1023.7556561086 903.0910633485 0.0) (10 1000.3120241784 877.2992182829 0.0) (10
1008.7885627124 817.3789104147 0.0) (10 1019.7080616209 763.6825402997 0.0) (10 1021.8703619908 742.8365384615 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1021.870361991 742.8365384615 0.0) (10 1050.4906696961 740.8083476252 0.0) (10 1068.3066707039
778.5917883527 0.0) (10 1052.036199095 803.1674208145 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1021.870361991 592.0050904977 0.0) (10 1016.1897645833 555.4389675051 0.0) (10 1068.8049927204
549.3423269813 0.0) (10 1063.3484162896 512.8195701357 0.0))
((0 . "LWPOLYLINE") (100 . "AcDbEntity") (8 . "PLANTS") (62 . 94) (370 . 13) (100 . "AcDbPolyline") (90 . 3) (70 . 0)
(43 . 0.0) (10 1021.870361991 505.2799773756) (10 1048.2653846154 505.4277149321) (10 1063.3484162896 512.8195701357))
((0 . "LWPOLYLINE") (100 . "AcDbEntity") (8 . "PLANTS") (62 . 94) (370 . 13) (100 . "AcDbPolyline") (90 . 2) (70 . 0)
(43 . 0.0) (10 1023.7556561086 4070.5132352941) (10 1055.8070135747 4068.6270361991))
((0 . "LWPOLYLINE") (100 . "AcDbEntity") (8 . "PLANTS") (62 . 94) (370 . 13) (100 . "AcDbPolyline") (90 . 2) (70 . 0)
(43 . 0.0) (10 1023.7556561086 4070.5132352941) (10 1025.6409502262 3993.2126696833))
((0 . "LWPOLYLINE") (100 . "AcDbEntity") (8 . "PLANTS") (62 . 94) (370 . 13) (100 . "AcDbPolyline") (90 . 2) (70 . 0)
(43 . 0.0) (10 1023.7556561086 4070.5132352941) (10 1025.6409502262 4128.9592760181))
((0 . "LWPOLYLINE") (100 . "AcDbEntity") (8 . "PLANTS") (62 . 94) (370 . 13) (100 . "AcDbPolyline") (90 . 3) (70 . 0)
(43 . 0.0) (10 1023.7556561086 903.0910633484) (10 1044.4946832579 882.5075791855) (10 1055.8070135747 878.5831447964))
((0 . "LWPOLYLINE") (100 . "AcDbEntity") (8 . "PLANTS") (62 . 94) (370 . 13) (100 . "AcDbPolyline") (90 . 2) (70 . 0)
(43 . 0.0) (10 1048.2653846154 935.1442307692) (10 1023.7556561086 903.0910633484))
((0 . "LWPOLYLINE") (100 . "AcDbEntity") (8 . "PLANTS") (62 . 94) (370 . 13) (100 . "AcDbPolyline") (90 . 2) (70 . 0)
(43 . 0.0) (10 1025.6409502262 4128.9592760181) (10 1025.6410158852 4153.0339871585))
((0 . "LWPOLYLINE") (100 . "AcDbEntity") (8 . "PLANTS") (62 . 94) (370 . 13) (100 . "AcDbPolyline") (90 . 2) (70 . 0)
(43 . 0.0) (10 1025.6409502262 4128.9592760181) (10 1067.1192307692 4132.7304298643))
((0 . "LWPOLYLINE") (100 . "AcDbEntity") (8 . "PLANTS") (62 . 94) (370 . 13) (100 . "AcDbPolyline") (90 . 2) (70 . 0)
(43 . 0.0) (10 1025.6409502262 3993.2126696833) (10 1078.4314479638 3993.2126696833))
((0 . "LWPOLYLINE") (100 . "AcDbEntity") (8 . "PLANTS") (62 . 94) (370 . 13) (100 . "AcDbPolyline") (90 . 2) (70 . 0)
(43 . 0.0) (10 1025.6409502262 3627.4505656109) (10 1055.8070135747 3627.4505656109))
((0 . "LWPOLYLINE") (100 . "AcDbEntity") (8 . "PLANTS") (62 . 94) (370 . 13) (100 . "AcDbPolyline") (90 . 3) (70 . 0)
(43 . 0.0) (10 1044.4947963801 3529.4117647059) (10 1023.0746606335 3514.3290723982) (10 1025.6409502262
3480.3924208145))
((0 . "LWPOLYLINE") (100 . "AcDbEntity") (8 . "PLANTS") (62 . 94) (370 . 13) (100 . "AcDbPolyline") (90 . 2) (70 . 0)
(43 . 0.0) (10 1025.6409502262 1172.7007918552) (10 1063.3484162896 1161.3885746606))
((0 . "LWPOLYLINE") (100 . "AcDbEntity") (8 . "PLANTS") (62 . 94) (370 . 13) (100 . "AcDbPolyline") (90 . 3) (70 . 0)
(43 . 0.0) (10 1025.6409502262 1172.7007918552) (10 1022.0183257919 1195.3252262443) (10 1029.4117647059
1225.4892533937))
((0 . "LWPOLYLINE") (100 . "AcDbEntity") (8 . "PLANTS") (62 . 94) (370 . 13) (100 . "AcDbPolyline") (90 . 2) (70 . 0)
(43 . 0.0) (10 1025.6409502262 690.0452488688) (10 1036.9531674208 693.8150452489))
((0 . "LWPOLYLINE") (100 . "AcDbEntity") (8 . "PLANTS") (62 . 94) (370 . 13) (100 . "AcDbPolyline") (90 . 2) (70 . 0)
(43 . 0.0) (10 1029.4117647059 3744.3438914027) (10 1048.2653846154 3748.1150452489))
((0 . "LWPOLYLINE") (100 . "AcDbEntity") (8 . "PLANTS") (62 . 94) (370 . 13) (100 . "AcDbPolyline") (90 . 2) (70 . 0)
(43 . 0.0) (10 1052.036199095 1225.4892533937) (10 1029.4117647059 1225.4892533937))
((0 . "LWPOLYLINE") (100 . "AcDbEntity") (8 . "PLANTS") (62 . 94) (370 . 13) (100 . "AcDbPolyline") (90 . 3) (70 . 0)
(43 . 0.0) (10 1103.117012086 3305.1326907291) (10 1048.2653846154 3303.3158371041) (10 1033.1825791855
3310.7091628959))
((0 . "LWPOLYLINE") (100 . "AcDbEntity") (8 . "PLANTS") (62 . 94) (370 . 13) (100 . "AcDbPolyline") (90 . 2) (70 . 0)
(43 . 0.0) (10 1036.9531674208 3932.8804298643) (10 1097.2850678733 3917.7983031674))
((0 . "LWPOLYLINE") (100 . "AcDbEntity") (8 . "PLANTS") (62 . 94) (370 . 13) (100 . "AcDbPolyline") (90 . 2) (70 . 0)
(43 . 0.0) (10 1044.4947963801 3529.4117647059) (10 1070.8898190045 3506.7873303167))
((0 . "LWPOLYLINE") (100 . "AcDbEntity") (8 . "PLANTS") (62 . 94) (370 . 13) (100 . "AcDbPolyline") (90 . 2) (70 . 0)
(43 . 0.0) (10 1048.2653846154 967.1945701357) (10 1048.2653846154 935.1442307692))
((0 . "LWPOLYLINE") (100 . "AcDbEntity") (8 . "PLANTS") (62 . 94) (370 . 13) (100 . "AcDbPolyline") (90 . 3) (70 . 0)
(43 . 0.0) (10 1048.2653846154 967.1945701357) (10 1048.4135746606 1018.0995475113) (10 1055.8070135747 1033.181561086))
((0 . "LWPOLYLINE") (100 . "AcDbEntity") (8 . "PLANTS") (62 . 94) (370 . 13) (100 . "AcDbPolyline") (90 . 2) (70 . 0)
(43 . 0.0) (10 1048.2653846154 967.1945701357) (10 1097.2850678733 969.0808823529))
((0 . "LWPOLYLINE") (100 . "AcDbEntity") (8 . "PLANTS") (62 . 94) (370 . 13) (100 . "AcDbPolyline") (90 . 3) (70 . 0)
(43 . 0.0) (10 1048.2653846154 935.1442307692) (10 1059.5777149321 931.5200226244) (10 1097.2850678733 931.3716063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1052.036199095 1225.4892533936 0.0) (10 1061.6261312431 1196.7821001698 0.0) (10 1107.0215804221
1172.9947027097 0.0) (10 1131.221719457 1199.0950226244 0.0))
((0 . "LWPOLYLINE") (100 . "AcDbEntity") (8 . "PLANTS") (62 . 94) (370 . 13) (100 . "AcDbPolyline") (90 . 3) (70 . 0)
(43 . 0.0) (10 1052.036199095 1225.4892533937) (10 1062.1442307692 1240.5740950226) (10 1067.1192307692
1259.4259049774))
((0 . "LWPOLYLINE") (100 . "AcDbEntity") (8 . "PLANTS") (62 . 94) (370 . 13) (100 . "AcDbPolyline") (90 . 3) (70 . 0)
(43 . 0.0) (10 1108.5972850679 776.7731900452) (10 1089.7436651584 790.6503393665) (10 1052.036199095 803.1674208145))
((0 . "LWPOLYLINE") (100 . "AcDbEntity") (8 . "PLANTS") (62 . 94) (370 . 13) (100 . "AcDbPolyline") (90 . 3) (70 . 0)
(43 . 0.0) (10 1052.036199095 803.1674208145) (10 1052.1841628959 852.0328054299) (10 1055.8070135747 855.9587104072))
((0 . "LWPOLYLINE") (100 . "AcDbEntity") (8 . "PLANTS") (62 . 94) (370 . 13) (100 . "AcDbPolyline") (90 . 2) (70 . 0)
(43 . 0.0) (10 1070.8898190045 4068.6270361991) (10 1055.8070135747 4068.6270361991))
((0 . "LWPOLYLINE") (100 . "AcDbEntity") (8 . "PLANTS") (62 . 94) (370 . 13) (100 . "AcDbPolyline") (90 . 3) (70 . 0)
(43 . 0.0) (10 1074.6606334842 4034.6903846154) (10 1057.0113122172 4049.7737556561) (10 1055.8070135747
4068.6270361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1151.9608597285 3766.9683257919 0.0) (10 1119.2553171603 3757.5654465213 0.0) (10 1083.3981118216
3767.2799097308 0.0) (10 1055.8070135747 3785.8216063348 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4483090182) (40
. 1) (40 . 1) (40 . 1) (40 . 1) (10 1055.8070135747 3785.8216063348 0.0) (10 1052.11514858 3808.4834645143 0.0) (10
1057.131008144 3859.6515946401 0.0) (10 1110.4186654774 3883.1522956864 0.0) (10 1097.2850678733 3917.7983031674 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1108.5972850679 3648.1900452489 0.0) (10 1114.9607562471 3610.9814152673 0.0) (10 1071.3663103109
3607.656112559 0.0) (10 1055.8070135747 3627.4505656109 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1108.5972850679 3648.1900452489 0.0) (10 1089.0572182883 3664.1715766168 0.0) (10 1057.0560346711
3652.1127649866 0.0) (10 1055.8070135747 3627.4505656109 0.0))
((0 . "LWPOLYLINE") (100 . "AcDbEntity") (8 . "PLANTS") (62 . 94) (370 . 13) (100 . "AcDbPolyline") (90 . 2) (70 . 0)
(43 . 0.0) (10 1067.1192307692 1259.4259049774) (10 1055.8070135747 1297.1351809955))
((0 . "LWPOLYLINE") (100 . "AcDbEntity") (8 . "PLANTS") (62 . 94) (370 . 13) (100 . "AcDbPolyline") (90 . 2) (70 . 0)
(43 . 0.0) (10 1063.3484162896 1319.7596153846) (10 1055.8070135747 1297.1351809955))
((0 . "LWPOLYLINE") (100 . "AcDbEntity") (8 . "PLANTS") (62 . 94) (370 . 13) (100 . "AcDbPolyline") (90 . 2) (70 . 0)
(43 . 0.0) (10 1055.8070135747 855.9587104072) (10 1055.8070135747 878.5831447964))
((0 . "LWPOLYLINE") (100 . "AcDbEntity") (8 . "PLANTS") (62 . 94) (370 . 13) (100 . "AcDbPolyline") (90 . 3) (70 . 0)
(43 . 0.0) (10 1119.9095022624 893.665158371) (10 1085.9728506787 893.5167420814) (10 1055.8070135747 878.5831447964))
((0 . "LWPOLYLINE") (100 . "AcDbEntity") (8 . "PLANTS") (62 . 94) (370 . 13) (100 . "AcDbPolyline") (90 . 3) (70 . 0)
(43 . 0.0) (10 1108.5972850679 837.1040723982) (10 1078.4314479638 851.1304298643) (10 1055.8070135747 855.9587104072))
((0 . "LWPOLYLINE") (100 . "AcDbEntity") (8 . "PLANTS") (62 . 94) (370 . 13) (100 . "AcDbPolyline") (90 . 2) (70 . 0)
(43 . 0.0) (10 1089.7436651584 1319.7596153846) (10 1063.3484162896 1319.7596153846))
((0 . "LWPOLYLINE") (100 . "AcDbEntity") (8 . "PLANTS") (62 . 94) (370 . 13) (100 . "AcDbPolyline") (90 . 2) (70 . 0)
(43 . 0.0) (10 1063.3484162896 1353.9853811347) (10 1063.3484162896 1319.7596153846))
((0 . "LWPOLYLINE") (100 . "AcDbEntity") (8 . "PLANTS") (62 . 94) (370 . 13) (100 . "AcDbPolyline") (90 . 3) (70 . 0)
(43 . 0.0) (10 1110.5297156383 507.4704766508) (10 1093.5142533937 505.4270361991) (10 1063.3484162896 512.8195701357))
((0 . "LWPOLYLINE") (100 . "AcDbEntity") (8 . "PLANTS") (62 . 94) (370 . 13) (100 . "AcDbPolyline") (90 . 2) (70 . 0)
(43 . 0.0) (10 1067.1192307692 4110.1059954751) (10 1067.1192307692 4132.7304298643))
((0 . "LWPOLYLINE") (100 . "AcDbEntity") (8 . "PLANTS") (62 . 94) (370 . 13) (100 . "AcDbPolyline") (90 . 3) (70 . 0)
(43 . 0.0) (10 1067.1192307692 4132.7304298643) (10 1074.6606334842 4144.0426470588) (10 1078.4314479638
4144.0426470588))
((0 . "LWPOLYLINE") (100 . "AcDbEntity") (8 . "PLANTS") (62 . 94) (370 . 13) (100 . "AcDbPolyline") (90 . 2) (70 . 0)
(43 . 0.0) (10 1070.8898190045 4068.6270361991) (10 1067.1192307692 4098.7937782805))
((0 . "LWPOLYLINE") (100 . "AcDbEntity") (8 . "PLANTS") (62 . 94) (370 . 13) (100 . "AcDbPolyline") (90 . 2) (70 . 0)
(43 . 0.0) (10 1093.5142533937 1259.4259049774) (10 1067.1192307692 1259.4259049774))
((0 . "LWPOLYLINE") (100 . "AcDbEntity") (8 . "PLANTS") (62 . 94) (370 . 13) (100 . "AcDbPolyline") (90 . 2) (70 . 0)
(43 . 0.0) (10 1070.8898190045 4068.6270361991) (10 1085.9728506787 4061.0859728507))
((0 . "LWPOLYLINE") (100 . "AcDbEntity") (8 . "PLANTS") (62 . 94) (370 . 13) (100 . "AcDbPolyline") (90 . 3) (70 . 0)
(43 . 0.0) (10 1074.6606334842 4034.6903846154) (10 1074.8085972851 4012.0728506787) (10 1078.4314479638
4004.5248868778))
((0 . "LWPOLYLINE") (100 . "AcDbEntity") (8 . "PLANTS") (62 . 94) (370 . 13) (100 . "AcDbPolyline") (90 . 2) (70 . 0)
(43 . 0.0) (10 1074.6606334842 4034.6903846154) (10 1082.2020361991 4038.4615384615))
((0 . "LWPOLYLINE") (100 . "AcDbEntity") (8 . "PLANTS") (62 . 94) (370 . 13) (100 . "AcDbPolyline") (90 . 3) (70 . 0)
(43 . 0.0) (10 1074.6606334842 1108.5972850679) (10 1078.5860859729 1102.2459276018) (10 1093.5142533937
1097.2850678733))
((0 . "LWPOLYLINE") (100 . "AcDbEntity") (8 . "PLANTS") (62 . 94) (370 . 13) (100 . "AcDbPolyline") (90 . 3) (70 . 0)
(43 . 0.0) (10 1097.2850678733 1142.5339366516) (10 1083.4063348416 1134.9866515837) (10 1074.6606334842
1108.5972850679))
((0 . "LWPOLYLINE") (100 . "AcDbEntity") (8 . "PLANTS") (62 . 94) (370 . 13) (100 . "AcDbPolyline") (90 . 2) (70 . 0)
(43 . 0.0) (10 1097.2850678733 4140.2714932127) (10 1078.4314479638 4144.0426470588))
((0 . "LWPOLYLINE") (100 . "AcDbEntity") (8 . "PLANTS") (62 . 94) (370 . 13) (100 . "AcDbPolyline") (90 . 2) (70 . 0)
(43 . 0.0) (10 1078.4332842522 4193.6434243639) (10 1078.4314479638 4144.0426470588))
((0 . "LWPOLYLINE") (100 . "AcDbEntity") (8 . "PLANTS") (62 . 94) (370 . 13) (100 . "AcDbPolyline") (90 . 2) (70 . 0)
(43 . 0.0) (10 1078.4314479638 4004.5248868778) (10 1078.4314479638 3993.2126696833))
((0 . "LWPOLYLINE") (100 . "AcDbEntity") (8 . "PLANTS") (62 . 94) (370 . 13) (100 . "AcDbPolyline") (90 . 3) (70 . 0)
(43 . 0.0) (10 1078.4314479638 4004.5248868778) (10 1100.9011312217 4015.9851809955) (10 1104.8264705882
4027.149321267))
((0 . "LWPOLYLINE") (100 . "AcDbEntity") (8 . "PLANTS") (62 . 94) (370 . 13) (100 . "AcDbPolyline") (90 . 3) (70 . 0)
(43 . 0.0) (10 1116.1386877828 3970.5882352941) (10 1089.8916289593 3979.1859728507) (10 1078.4314479638
3993.2126696833))
((0 . "LWPOLYLINE") (100 . "AcDbEntity") (8 . "PLANTS") (62 . 94) (370 . 13) (100 . "AcDbPolyline") (90 . 3) (70 . 0)
(43 . 0.0) (10 1081.7131328567 1368.1120861863) (10 1089.5889140271 1357.4660633484) (10 1089.7436651584
1319.7596153846))
((0 . "LWPOLYLINE") (100 . "AcDbEntity") (8 . "PLANTS") (62 . 94) (370 . 13) (100 . "AcDbPolyline") (90 . 2) (70 . 0)
(43 . 0.0) (10 1082.2020361991 4038.4615384615) (10 1104.8264705882 4027.149321267))
((0 . "LWPOLYLINE") (100 . "AcDbEntity") (8 . "PLANTS") (62 . 94) (370 . 13) (100 . "AcDbPolyline") (90 . 2) (70 . 0)
(43 . 0.0) (10 1082.2020361991 4038.4615384615) (10 1085.9728506787 4061.0859728507))
((0 . "LWPOLYLINE") (100 . "AcDbEntity") (8 . "PLANTS") (62 . 94) (370 . 13) (100 . "AcDbPolyline") (90 . 2) (70 . 0)
(43 . 0.0) (10 1085.9728506787 4061.0859728507) (10 1104.8264705882 4064.8571266968))
((0 . "LWPOLYLINE") (100 . "AcDbEntity") (8 . "PLANTS") (62 . 94) (370 . 13) (100 . "AcDbPolyline") (90 . 3) (70 . 0)
(43 . 0.0) (10 1089.7436651584 1319.7596153846) (10 1097.1305429864 1270.7381221719) (10 1093.5142533937
1259.4259049774))
((0 . "LWPOLYLINE") (100 . "AcDbEntity") (8 . "PLANTS") (62 . 94) (370 . 13) (100 . "AcDbPolyline") (90 . 2) (70 . 0)
(43 . 0.0) (10 1089.7436651584 478.882918552) (10 1089.7436651584 486.4253393665))
((0 . "LWPOLYLINE") (100 . "AcDbEntity") (8 . "PLANTS") (62 . 94) (370 . 13) (100 . "AcDbPolyline") (90 . 3) (70 . 0)
(43 . 0.0) (10 1093.5142533937 1259.4259049774) (10 1109.6535067873 1225.4892533937) (10 1131.221719457
1206.6374434389))
((0 . "LWPOLYLINE") (100 . "AcDbEntity") (8 . "PLANTS") (62 . 94) (370 . 13) (100 . "AcDbPolyline") (90 . 3) (70 . 0)
(43 . 0.0) (10 1093.5142533937 1097.2850678733) (10 1085.9794117647 1021.8693438914) (10 1097.2850678733
969.0808823529))
((0 . "LWPOLYLINE") (100 . "AcDbEntity") (8 . "PLANTS") (62 . 94) (370 . 13) (100 . "AcDbPolyline") (90 . 3) (70 . 0)
(43 . 0.0) (10 1180.2414027149 1119.9095022624) (10 1138.7631221719 1118.8600678733) (10 1093.5142533937
1097.2850678733))
((0 . "LWPOLYLINE") (100 . "AcDbEntity") (8 . "PLANTS") (62 . 94) (370 . 13) (100 . "AcDbPolyline") (90 . 2) (70 . 0)
(43 . 0.0) (10 1097.2850678733 4140.2714932127) (10 1134.9924208145 4140.2714932127))
((0 . "LWPOLYLINE") (100 . "AcDbEntity") (8 . "PLANTS") (62 . 94) (370 . 13) (100 . "AcDbPolyline") (90 . 3) (70 . 0)
(43 . 0.0) (10 1097.2850678733 4140.2714932127) (10 1104.6785067873 4095.0226244344) (10 1104.8264705882
4064.8571266968))
((0 . "LWPOLYLINE") (100 . "AcDbEntity") (8 . "PLANTS") (62 . 94) (370 . 13) (100 . "AcDbPolyline") (90 . 3) (70 . 0)
(43 . 0.0) (10 1134.9925339367 3925.3393665158) (10 1123.6802036199 3917.9522624434) (10 1097.2850678733
3917.7983031674))
((0 . "LWPOLYLINE") (100 . "AcDbEntity") (8 . "PLANTS") (62 . 94) (370 . 13) (100 . "AcDbPolyline") (90 . 3) (70 . 0)
(43 . 0.0) (10 1101.0558823529 965.3082579186) (10 1101.0558823529 969.0808823529) (10 1097.2850678733 969.0808823529))
((0 . "LWPOLYLINE") (100 . "AcDbEntity") (8 . "PLANTS") (62 . 94) (370 . 13) (100 . "AcDbPolyline") (90 . 2) (70 . 0)
(43 . 0.0) (10 1097.2850678733 969.0808823529) (10 1101.0558823529 965.3082579186))
((0 . "LWPOLYLINE") (100 . "AcDbEntity") (8 . "PLANTS") (62 . 94) (370 . 13) (100 . "AcDbPolyline") (90 . 2) (70 . 0)
(43 . 0.0) (10 1097.2850678733 931.3716063348) (10 1119.9095022624 927.6018099548))
((0 . "LWPOLYLINE") (100 . "AcDbEntity") (8 . "PLANTS") (62 . 94) (370 . 13) (100 . "AcDbPolyline") (90 . 2) (70 . 0)
(43 . 0.0) (10 1097.2850678733 931.3716063348) (10 1101.0558823529 965.3082579186))
((0 . "LWPOLYLINE") (100 . "AcDbEntity") (8 . "PLANTS") (62 . 94) (370 . 13) (100 . "AcDbPolyline") (90 . 3) (70 . 0)
(43 . 0.0) (10 1108.5972850679 3665.1583710407) (10 1102.2535067873 3669.0834841629) (10 1101.0558823529
3687.7828054299))
((0 . "LWPOLYLINE") (100 . "AcDbEntity") (8 . "PLANTS") (62 . 94) (370 . 13) (100 . "AcDbPolyline") (90 . 3) (70 . 0)
(43 . 0.0) (10 1127.4509049774 3702.8661764706) (10 1108.603959276 3697.89739819) (10 1101.0558823529 3687.7828054299))
((0 . "LWPOLYLINE") (100 . "AcDbEntity") (8 . "PLANTS") (62 . 94) (370 . 13) (100 . "AcDbPolyline") (90 . 3) (70 . 0)
(43 . 0.0) (10 1101.0558823529 965.3082579186) (10 1127.4509049774 960.3335972851) (10 1138.7631221719 950.2262443439))
((0 . "LWPOLYLINE") (100 . "AcDbEntity") (8 . "PLANTS") (62 . 94) (370 . 13) (100 . "AcDbPolyline") (90 . 2) (70 . 0)
(43 . 0.0) (10 1112.3680995475 4057.3148190045) (10 1104.8264705882 4064.8571266968))
((0 . "LWPOLYLINE") (100 . "AcDbEntity") (8 . "PLANTS") (62 . 94) (370 . 13) (100 . "AcDbPolyline") (90 . 2) (70 . 0)
(43 . 0.0) (10 1112.3680995475 4030.9204751131) (10 1104.8264705882 4027.149321267))
((0 . "LWPOLYLINE") (100 . "AcDbEntity") (8 . "PLANTS") (62 . 94) (370 . 13) (100 . "AcDbPolyline") (90 . 2) (70 . 0)
(43 . 0.0) (10 1108.5972850679 3648.1900452489) (10 1108.5972850679 3665.1583710407))
((0 . "LWPOLYLINE") (100 . "AcDbEntity") (8 . "PLANTS") (62 . 94) (370 . 13) (100 . "AcDbPolyline") (90 . 3) (70 . 0)
(43 . 0.0) (10 1127.4509049774 3702.8661764706) (10 1120.8045248869 3680.2417420814) (10 1108.5972850679
3665.1583710407))
((0 . "LWPOLYLINE") (100 . "AcDbEntity") (8 . "PLANTS") (62 . 94) (370 . 13) (100 . "AcDbPolyline") (90 . 2) (70 . 0)
(43 . 0.0) (10 1108.5972850679 3648.1900452489) (10 1138.7631221719 3646.3050904977))
((0 . "LWPOLYLINE") (100 . "AcDbEntity") (8 . "PLANTS") (62 . 94) (370 . 13) (100 . "AcDbPolyline") (90 . 3) (70 . 0)
(43 . 0.0) (10 1131.221719457 818.2494343891) (10 1112.5227375566 826.8481900452) (10 1108.5972850679 837.1040723982))
((0 . "LWPOLYLINE") (100 . "AcDbEntity") (8 . "PLANTS") (62 . 94) (370 . 13) (100 . "AcDbPolyline") (90 . 2) (70 . 0)
(43 . 0.0) (10 1146.3047511312 863.4983031674) (10 1108.5972850679 837.1040723982))
((0 . "LWPOLYLINE") (100 . "AcDbEntity") (8 . "PLANTS") (62 . 94) (370 . 13) (100 . "AcDbPolyline") (90 . 3) (70 . 0)
(43 . 0.0) (10 1108.5972850679 776.7731900452) (10 1104.8395927602 761.6883484163) (10 1108.5972850679 723.9819004525))
((0 . "LWPOLYLINE") (100 . "AcDbEntity") (8 . "PLANTS") (62 . 94) (370 . 13) (100 . "AcDbPolyline") (90 . 2) (70 . 0)
(43 . 0.0) (10 1131.221719457 780.5429864253) (10 1108.5972850679 776.7731900452))
((0 . "LWPOLYLINE") (100 . "AcDbEntity") (8 . "PLANTS") (62 . 94) (370 . 13) (100 . "AcDbPolyline") (90 . 2) (70 . 0)
(43 . 0.0) (10 1108.5972850679 663.6510180995) (10 1119.9095022624 671.1906108597))
((0 . "LWPOLYLINE") (100 . "AcDbEntity") (8 . "PLANTS") (62 . 94) (370 . 13) (100 . "AcDbPolyline") (90 . 2) (70 . 0)
(43 . 0.0) (10 1112.3680995475 4057.3148190045) (10 1134.9924208145 4057.3148190045))
((0 . "LWPOLYLINE") (100 . "AcDbEntity") (8 . "PLANTS") (62 . 94) (370 . 13) (100 . "AcDbPolyline") (90 . 2) (70 . 0)
(43 . 0.0) (10 1112.3680995475 4057.3148190045) (10 1112.3680995475 4030.9204751131))
((0 . "LWPOLYLINE") (100 . "AcDbEntity") (8 . "PLANTS") (62 . 94) (370 . 13) (100 . "AcDbPolyline") (90 . 2) (70 . 0)
(43 . 0.0) (10 1112.3680995475 4030.9204751131) (10 1148.1900452489 4032.8054298643))
((0 . "LWPOLYLINE") (100 . "AcDbEntity") (8 . "PLANTS") (62 . 94) (370 . 13) (100 . "AcDbPolyline") (90 . 2) (70 . 0)
(43 . 0.0) (10 1116.1386877828 3487.9333710407) (10 1112.3680995475 3480.3924208145))
((0 . "LWPOLYLINE") (100 . "AcDbEntity") (8 . "PLANTS") (62 . 94) (370 . 13) (100 . "AcDbPolyline") (90 . 3) (70 . 0)
(43 . 0.0) (10 1134.9925339367 3925.3393665158) (10 1120.9657239819 3944.1926470588) (10 1116.1386877828
3970.5882352941))
((0 . "LWPOLYLINE") (100 . "AcDbEntity") (8 . "PLANTS") (62 . 94) (370 . 13) (100 . "AcDbPolyline") (90 . 2) (70 . 0)
(43 . 0.0) (10 1116.1386877828 3970.5882352941) (10 1148.1900452489 4032.8054298643))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3922922868) (40
. 1) (40 . 1) (40 . 1) (40 . 1) (10 1116.1386877829 3487.9333710407 0.0) (10 1103.9585461276 3509.7176695105 0.0) (10
1104.0709165549 3564.1170455645 0.0) (10 1146.0041722727 3611.2928971395 0.0) (10 1138.763122172 3646.3050904977 0.0))
((0 . "LWPOLYLINE") (100 . "AcDbEntity") (8 . "PLANTS") (62 . 94) (370 . 13) (100 . "AcDbPolyline") (90 . 2) (70 . 0)
(43 . 0.0) (10 1116.1386877828 3487.9333710407) (10 1132.2329736242 3490.2328700481))
((0 . "LWPOLYLINE") (100 . "AcDbEntity") (8 . "PLANTS") (62 . 94) (370 . 13) (100 . "AcDbPolyline") (90 . 2) (70 . 0)
(43 . 0.0) (10 1116.1386877828 618.4021493213) (10 1128.9951181314 621.6154373151))
((0 . "LWPOLYLINE") (100 . "AcDbEntity") (8 . "PLANTS") (62 . 94) (370 . 13) (100 . "AcDbPolyline") (90 . 2) (70 . 0)
(43 . 0.0) (10 1119.9095022624 893.665158371) (10 1119.9095022624 927.6018099548))
((0 . "LWPOLYLINE") (100 . "AcDbEntity") (8 . "PLANTS") (62 . 94) (370 . 13) (100 . "AcDbPolyline") (90 . 2) (70 . 0)
(43 . 0.0) (10 1119.9095022624 927.6018099548) (10 1138.7631221719 950.2262443439))
((0 . "LWPOLYLINE") (100 . "AcDbEntity") (8 . "PLANTS") (62 . 94) (370 . 13) (100 . "AcDbPolyline") (90 . 3) (70 . 0)
(43 . 0.0) (10 1119.9095022624 893.665158371) (10 1134.9924208145 892.4671945701) (10 1146.3047511312 886.1227375566))
((0 . "LWPOLYLINE") (100 . "AcDbEntity") (8 . "PLANTS") (62 . 94) (370 . 13) (100 . "AcDbPolyline") (90 . 2) (70 . 0)
(43 . 0.0) (10 1119.9095022624 671.1906108597) (10 1132.3562181514 663.7225514541))
((0 . "LWPOLYLINE") (100 . "AcDbEntity") (8 . "PLANTS") (62 . 94) (370 . 13) (100 . "AcDbPolyline") (90 . 3) (70 . 0)
(43 . 0.0) (10 1119.9095022624 671.1906108597) (10 1121.113800905 686.1201357466) (10 1134.6138786779 692.0060208277))
((0 . "LWPOLYLINE") (100 . "AcDbEntity") (8 . "PLANTS") (62 . 94) (370 . 13) (100 . "AcDbPolyline") (90 . 3) (70 . 0)
(43 . 0.0) (10 1123.6803167421 3838.6127828054) (10 1124.8846153846 3846.0123303167) (10 1142.5339366516
3861.2372171946))
((0 . "LWPOLYLINE") (100 . "AcDbEntity") (8 . "PLANTS") (62 . 94) (370 . 13) (100 . "AcDbPolyline") (90 . 3) (70 . 0)
(43 . 0.0) (10 1151.7905416169 3735.2457357332) (10 1138.9113122172 3725.4899321267) (10 1127.4509049774
3702.8661764706))
((0 . "LWPOLYLINE") (100 . "AcDbEntity") (8 . "PLANTS") (62 . 94) (370 . 13) (100 . "AcDbPolyline") (90 . 2) (70 . 0)
(43 . 0.0) (10 1131.221719457 1199.0950226244) (10 1131.221719457 1206.6374434389))
((0 . "LWPOLYLINE") (100 . "AcDbEntity") (8 . "PLANTS") (62 . 94) (370 . 13) (100 . "AcDbPolyline") (90 . 3) (70 . 0)
(43 . 0.0) (10 1142.5339366516 1289.592760181) (10 1142.3792986425 1221.7194570136) (10 1131.221719457 1206.6374434389))
((0 . "LWPOLYLINE") (100 . "AcDbEntity") (8 . "PLANTS") (62 . 94) (370 . 13) (100 . "AcDbPolyline") (90 . 3) (70 . 0)
(43 . 0.0) (10 1168.9291855204 1180.2403846154) (10 1146.3047511312 1185.2164027149) (10 1131.221719457
1199.0950226244))
((0 . "LWPOLYLINE") (100 . "AcDbEntity") (8 . "PLANTS") (62 . 94) (370 . 13) (100 . "AcDbPolyline") (90 . 3) (70 . 0)
(43 . 0.0) (10 1131.221719457 1033.181561086) (10 1150.0753393665 1018.2541855204) (10 1210.407239819 1021.8693438914))
((0 . "LWPOLYLINE") (100 . "AcDbEntity") (8 . "PLANTS") (62 . 94) (370 . 13) (100 . "AcDbPolyline") (90 . 2) (70 . 0)
(43 . 0.0) (10 1131.221719457 780.5429864253) (10 1131.221719457 818.2494343891))
((0 . "LWPOLYLINE") (100 . "AcDbEntity") (8 . "PLANTS") (62 . 94) (370 . 13) (100 . "AcDbPolyline") (90 . 2) (70 . 0)
(43 . 0.0) (10 1146.117818699 836.1248249811) (10 1131.221719457 818.2494343891))
((0 . "LWPOLYLINE") (100 . "AcDbEntity") (8 . "PLANTS") (62 . 94) (370 . 13) (100 . "AcDbPolyline") (90 . 3) (70 . 0)
(43 . 0.0) (10 1134.9925339367 776.7731900452) (10 1134.9925339367 780.5429864253) (10 1131.221719457 780.5429864253))
((0 . "LWPOLYLINE") (100 . "AcDbEntity") (8 . "PLANTS") (62 . 94) (370 . 13) (100 . "AcDbPolyline") (90 . 2) (70 . 0)
(43 . 0.0) (10 1134.9925339367 776.7731900452) (10 1131.221719457 780.5429864253))
((0 . "LWPOLYLINE") (100 . "AcDbEntity") (8 . "PLANTS") (62 . 94) (370 . 13) (100 . "AcDbPolyline") (90 . 2) (70 . 0)
(43 . 0.0) (10 1134.9924208145 4121.4182126697) (10 1134.9924208145 4140.2714932127))
((0 . "LWPOLYLINE") (100 . "AcDbEntity") (8 . "PLANTS") (62 . 94) (370 . 13) (100 . "AcDbPolyline") (90 . 3) (70 . 0)
(43 . 0.0) (10 1135.4143604066 4167.0824813442) (10 1134.9924208145 4166.6601809955) (10 1134.9924208145
4140.2714932127))
((0 . "LWPOLYLINE") (100 . "AcDbEntity") (8 . "PLANTS") (62 . 94) (370 . 13) (100 . "AcDbPolyline") (90 . 3) (70 . 0)
(43 . 0.0) (10 1134.9924208145 4121.4182126697) (10 1153.6916289593 4120.2134615385) (10 1172.6997737557
4095.0226244344))
((0 . "LWPOLYLINE") (100 . "AcDbEntity") (8 . "PLANTS") (62 . 94) (370 . 13) (100 . "AcDbPolyline") (90 . 2) (70 . 0)
(43 . 0.0) (10 1134.9924208145 4121.4182126697) (10 1134.9924208145 4057.3148190045))
((0 . "LWPOLYLINE") (100 . "AcDbEntity") (8 . "PLANTS") (62 . 94) (370 . 13) (100 . "AcDbPolyline") (90 . 2) (70 . 0)
(43 . 0.0) (10 1146.3047511312 4049.7737556561) (10 1134.9924208145 4057.3148190045))
((0 . "LWPOLYLINE") (100 . "AcDbEntity") (8 . "PLANTS") (62 . 94) (370 . 13) (100 . "AcDbPolyline") (90 . 2) (70 . 0)
(43 . 0.0) (10 1134.9925339367 3925.3393665158) (10 1168.9291855204 3925.3393665158))
((0 . "LWPOLYLINE") (100 . "AcDbEntity") (8 . "PLANTS") (62 . 94) (370 . 13) (100 . "AcDbPolyline") (90 . 2) (70 . 0)
(43 . 0.0) (10 1141.3207805062 776.0285965104) (10 1134.9925339367 776.7731900452))
((0 . "LWPOLYLINE") (100 . "AcDbEntity") (8 . "PLANTS") (62 . 94) (370 . 13) (100 . "AcDbPolyline") (90 . 3) (70 . 0)
(43 . 0.0) (10 1134.9925339367 776.7731900452) (10 1135.1404977376 712.6696832579) (10 1135.9337486189 708.541058144))
((0 . "LWPOLYLINE") (100 . "AcDbEntity") (8 . "PLANTS") (62 . 94) (370 . 13) (100 . "AcDbPolyline") (90 . 2) (70 . 0)
(43 . 0.0) (10 1144.6910666091 3646.3050904977) (10 1138.7631221719 3646.3050904977))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1133.2004355668 1341.4124094523 0.0) (10 1121.9591726686 1326.2041639033 0.0) (10 1125.3207134942
1298.8331301153 0.0) (10 1142.5339366516 1289.592760181 0.0))
((0 . "LWPOLYLINE") (100 . "AcDbEntity") (8 . "PLANTS") (62 . 94) (370 . 13) (100 . "AcDbPolyline") (90 . 2) (70 . 0)
(43 . 0.0) (10 1172.6997737557 950.2262443439) (10 1138.7631221719 950.2262443439))
((0 . "LWPOLYLINE") (100 . "AcDbEntity") (8 . "PLANTS") (62 . 94) (370 . 13) (100 . "AcDbPolyline") (90 . 2) (70 . 0)
(43 . 0.0) (10 1157.6168552036 1308.44739819) (10 1142.5339366516 1289.592760181))
((0 . "LWPOLYLINE") (100 . "AcDbEntity") (8 . "PLANTS") (62 . 94) (370 . 13) (100 . "AcDbPolyline") (90 . 2) (70 . 0)
(43 . 0.0) (10 1146.3047511312 4049.7737556561) (10 1148.1900452489 4032.8054298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1146.3047511312 4049.7737556561 0.0) (10 1163.9516282142 4059.7676698138 0.0) (10 1156.5549306428
4083.5652854498 0.0) (10 1172.6997737557 4095.0226244344 0.0))
((0 . "LWPOLYLINE") (100 . "AcDbEntity") (8 . "PLANTS") (62 . 94) (370 . 13) (100 . "AcDbPolyline") (90 . 2) (70 . 0)
(43 . 0.0) (10 1146.3047511312 863.4983031674) (10 1146.3047511312 886.1227375566))
((0 . "LWPOLYLINE") (100 . "AcDbEntity") (8 . "PLANTS") (62 . 94) (370 . 13) (100 . "AcDbPolyline") (90 . 2) (70 . 0)
(43 . 0.0) (10 1150.2669391659 888.104084164) (10 1146.3047511312 886.1227375566))
((0 . "LWPOLYLINE") (100 . "AcDbEntity") (8 . "PLANTS") (62 . 94) (370 . 13) (100 . "AcDbPolyline") (90 . 2) (70 . 0)
(43 . 0.0) (10 1146.3047511312 863.4983031674) (10 1147.6557661455 855.391888825))
((0 . "LWPOLYLINE") (100 . "AcDbEntity") (8 . "PLANTS") (62 . 94) (370 . 13) (100 . "AcDbPolyline") (90 . 2) (70 . 0)
(43 . 0.0) (10 1195.3242081448 4042.2326923077) (10 1148.1900452489 4032.8054298643))
((0 . "LWPOLYLINE") (100 . "AcDbEntity") (8 . "PLANTS") (62 . 94) (370 . 13) (100 . "AcDbPolyline") (90 . 2) (70 . 0)
(43 . 0.0) (10 1151.9608597285 3766.9683257919) (10 1202.8658371041 3766.9683257919))
((0 . "LWPOLYLINE") (100 . "AcDbEntity") (8 . "PLANTS") (62 . 94) (370 . 13) (100 . "AcDbPolyline") (90 . 2) (70 . 0)
(43 . 0.0) (10 1151.9608597285 3766.9683257919) (10 1153.3748497591 3744.3438914027))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1151.9608597285 3766.9683257919 0.0) (10 1145.8680901615 3794.9817865719 0.0) (10 1168.5072768481
3824.5257379979 0.0) (10 1195.3242081448 3831.0704751131 0.0))
((0 . "LWPOLYLINE") (100 . "AcDbEntity") (8 . "PLANTS") (62 . 94) (370 . 13) (100 . "AcDbPolyline") (90 . 3) (70 . 0)
(43 . 0.0) (10 1168.9291855204 3925.3393665158) (10 1177.5201357466 3906.6400452489) (10 1184.0119909502
3902.7149321267))
((0 . "LWPOLYLINE") (100 . "AcDbEntity") (8 . "PLANTS") (62 . 94) (370 . 13) (100 . "AcDbPolyline") (90 . 2) (70 . 0)
(43 . 0.0) (10 1168.9291855204 3925.3393665158) (10 1180.2414027149 3947.963800905))
((0 . "LWPOLYLINE") (100 . "AcDbEntity") (8 . "PLANTS") (62 . 94) (370 . 13) (100 . "AcDbPolyline") (90 . 3) (70 . 0)
(43 . 0.0) (10 1168.9291855204 1180.2403846154) (10 1169.0838235294 1146.3037330317) (10 1180.2414027149
1131.221719457))
((0 . "LWPOLYLINE") (100 . "AcDbEntity") (8 . "PLANTS") (62 . 94) (370 . 13) (100 . "AcDbPolyline") (90 . 3) (70 . 0)
(43 . 0.0) (10 1199.0950226244 1259.4259049774) (10 1179.0436651584 1195.3252262443) (10 1168.9291855204
1180.2403846154))
((0 . "LWPOLYLINE") (100 . "AcDbEntity") (8 . "PLANTS") (62 . 94) (370 . 13) (100 . "AcDbPolyline") (90 . 2) (70 . 0)
(43 . 0.0) (10 1172.6997737557 4095.0226244344) (10 1199.5559088074 4098.0069676818))
((0 . "LWPOLYLINE") (100 . "AcDbEntity") (8 . "PLANTS") (62 . 94) (370 . 13) (100 . "AcDbPolyline") (90 . 2) (70 . 0)
(43 . 0.0) (10 1172.6997737557 950.2262443439) (10 1176.4705882353 931.3716063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1172.6997737557 950.2262443439 0.0) (10 1195.5586866802 964.7048839548 0.0) (10 1219.1339657594
992.2638442851 0.0) (10 1210.407239819 1021.8693438914 0.0))
((0 . "LWPOLYLINE") (100 . "AcDbEntity") (8 . "PLANTS") (62 . 94) (370 . 13) (100 . "AcDbPolyline") (90 . 3) (70 . 0)
(43 . 0.0) (10 1248.1147058824 923.8320135747) (10 1221.7194570136 931.2245475113) (10 1176.4705882353 931.3716063348))
((0 . "LWPOLYLINE") (100 . "AcDbEntity") (8 . "PLANTS") (62 . 94) (370 . 13) (100 . "AcDbPolyline") (90 . 2) (70 . 0)
(43 . 0.0) (10 1176.4705882353 916.2895927602) (10 1176.4705882353 931.3716063348))
((0 . "LWPOLYLINE") (100 . "AcDbEntity") (8 . "PLANTS") (62 . 94) (370 . 13) (100 . "AcDbPolyline") (90 . 2) (70 . 0)
(43 . 0.0) (10 1180.2414027149 3959.2760180995) (10 1180.2414027149 3947.963800905))
((0 . "LWPOLYLINE") (100 . "AcDbEntity") (8 . "PLANTS") (62 . 94) (370 . 13) (100 . "AcDbPolyline") (90 . 3) (70 . 0)
(43 . 0.0) (10 1255.6561085973 3959.2760180995) (10 1221.7194570136 3948.1118778281) (10 1180.2414027149
3947.963800905))
((0 . "LWPOLYLINE") (100 . "AcDbEntity") (8 . "PLANTS") (62 . 94) (370 . 13) (100 . "AcDbPolyline") (90 . 2) (70 . 0)
(43 . 0.0) (10 1180.2414027149 1119.9095022624) (10 1180.2414027149 1131.221719457))
((0 . "LWPOLYLINE") (100 . "AcDbEntity") (8 . "PLANTS") (62 . 94) (370 . 13) (100 . "AcDbPolyline") (90 . 2) (70 . 0)
(43 . 0.0) (10 1199.0950226244 1138.7641402715) (10 1180.2414027149 1131.221719457))
((0 . "LWPOLYLINE") (100 . "AcDbEntity") (8 . "PLANTS") (62 . 94) (370 . 13) (100 . "AcDbPolyline") (90 . 3) (70 . 0)
(43 . 0.0) (10 1180.2414027149 1119.9095022624) (10 1199.0950226244 1098.3414027149) (10 1221.7194570136
1089.7426470588))
((0 . "LWPOLYLINE") (100 . "AcDbEntity") (8 . "PLANTS") (62 . 94) (370 . 13) (100 . "AcDbPolyline") (90 . 3) (70 . 0)
(43 . 0.0) (10 1248.1147058824 3883.8616515837) (10 1210.407239819 3897.8942307692) (10 1184.0119909502
3902.7149321267))
((0 . "LWPOLYLINE") (100 . "AcDbEntity") (8 . "PLANTS") (62 . 94) (370 . 13) (100 . "AcDbPolyline") (90 . 3) (70 . 0)
(43 . 0.0) (10 1195.3242081448 3842.3826923077) (10 1184.1600678733 3887.631561086) (10 1184.0119909502
3902.7149321267))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1195.3242081448 4042.2326923077 0.0) (10 1202.0818858581 4010.2185654238 0.0) (10 1249.173082815
4012.792910972 0.0) (10 1240.5730769231 4049.7737556561 0.0))
((0 . "LWPOLYLINE") (100 . "AcDbEntity") (8 . "PLANTS") (62 . 94) (370 . 13) (100 . "AcDbPolyline") (90 . 3) (70 . 0)
(43 . 0.0) (10 1195.3242081448 4042.2326923077) (10 1195.4722850679 4064.8571266968) (10 1204.5930523063
4092.5823516061))
((0 . "LWPOLYLINE") (100 . "AcDbEntity") (8 . "PLANTS") (62 . 94) (370 . 13) (100 . "AcDbPolyline") (90 . 2) (70 . 0)
(43 . 0.0) (10 1195.3242081448 3842.3826923077) (10 1248.1147058824 3842.3826923077))
((0 . "LWPOLYLINE") (100 . "AcDbEntity") (8 . "PLANTS") (62 . 94) (370 . 13) (100 . "AcDbPolyline") (90 . 2) (70 . 0)
(43 . 0.0) (10 1195.3242081448 3842.3826923077) (10 1195.3242081448 3831.0704751131))
((0 . "LWPOLYLINE") (100 . "AcDbEntity") (8 . "PLANTS") (62 . 94) (370 . 13) (100 . "AcDbPolyline") (90 . 3) (70 . 0)
(43 . 0.0) (10 1202.8658371041 3766.9683257919) (10 1202.717760181 3812.2171945701) (10 1195.3242081448
3831.0704751131))
((0 . "LWPOLYLINE") (100 . "AcDbEntity") (8 . "PLANTS") (62 . 94) (370 . 13) (100 . "AcDbPolyline") (90 . 2) (70 . 0)
(43 . 0.0) (10 1199.0950226244 1259.4259049774) (10 1199.0950226244 1270.4490080056))
((0 . "LWPOLYLINE") (100 . "AcDbEntity") (8 . "PLANTS") (62 . 94) (370 . 13) (100 . "AcDbPolyline") (90 . 2) (70 . 0)
(43 . 0.0) (10 1199.0950226244 1259.4259049774) (10 1207.2396927301 1261.6778248149))
((0 . "LWPOLYLINE") (100 . "AcDbEntity") (8 . "PLANTS") (62 . 94) (370 . 13) (100 . "AcDbPolyline") (90 . 2) (70 . 0)
(43 . 0.0) (10 1199.0950226244 1138.7641402715) (10 1225.4902714932 1138.7641402715))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1199.0950226244 1138.7641402715 0.0) (10 1200.5832720451 1159.210065896 0.0) (10 1216.3437264897
1177.0039086712 0.0) (10 1233.0316742081 1187.7828054299 0.0))
((0 . "LWPOLYLINE") (100 . "AcDbEntity") (8 . "PLANTS") (62 . 94) (370 . 13) (100 . "AcDbPolyline") (90 . 2) (70 . 0)
(43 . 0.0) (10 1202.8658371041 3766.9683257919) (10 1233.0316742081 3763.1971719457))
((0 . "LWPOLYLINE") (100 . "AcDbEntity") (8 . "PLANTS") (62 . 94) (370 . 13) (100 . "AcDbPolyline") (90 . 2) (70 . 0)
(43 . 0.0) (10 1221.7194570136 1044.4937782805) (10 1210.407239819 1021.8693438914))
((0 . "LWPOLYLINE") (100 . "AcDbEntity") (8 . "PLANTS") (62 . 94) (370 . 13) (100 . "AcDbPolyline") (90 . 2) (70 . 0)
(43 . 0.0) (10 1221.7194570136 1044.4937782805) (10 1221.7194570136 1089.7426470588))
((0 . "LWPOLYLINE") (100 . "AcDbEntity") (8 . "PLANTS") (62 . 94) (370 . 13) (100 . "AcDbPolyline") (90 . 3) (70 . 0)
(43 . 0.0) (10 1251.8852941176 1108.5972850679) (10 1244.1958144796 1094.7186651584) (10 1221.7194570136
1089.7426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1221.7194570136 1044.4937782805 0.0) (10 1244.8508830379 1043.3225103441 0.0) (10 1258.4183451426
1016.3981288596 0.0) (10 1255.6561085973 995.4751131222 0.0))
((0 . "LWPOLYLINE") (100 . "AcDbEntity") (8 . "PLANTS") (62 . 94) (370 . 13) (100 . "AcDbPolyline") (90 . 2) (70 . 0)
(43 . 0.0) (10 1251.8852941176 1108.5972850679) (10 1225.4902714932 1138.7641402715))
((0 . "LWPOLYLINE") (100 . "AcDbEntity") (8 . "PLANTS") (62 . 94) (370 . 13) (100 . "AcDbPolyline") (90 . 3) (70 . 0)
(43 . 0.0) (10 1282.0513574661 1176.4705882353) (10 1244.3438914027 1160.1899321267) (10 1225.4902714932
1138.7641402715))
((0 . "LWPOLYLINE") (100 . "AcDbEntity") (8 . "PLANTS") (62 . 94) (370 . 13) (100 . "AcDbPolyline") (90 . 2) (70 . 0)
(43 . 0.0) (10 1233.0316742081 3763.1971719457) (10 1240.4251131222 3744.3438914027))
((0 . "LWPOLYLINE") (100 . "AcDbEntity") (8 . "PLANTS") (62 . 94) (370 . 13) (100 . "AcDbPolyline") (90 . 2) (70 . 0)
(43 . 0.0) (10 1233.0316742081 3763.1971719457) (10 1248.1147058824 3774.5093891403))
((0 . "LWPOLYLINE") (100 . "AcDbEntity") (8 . "PLANTS") (62 . 94) (370 . 13) (100 . "AcDbPolyline") (90 . 2) (70 . 0)
(43 . 0.0) (10 1248.1147058824 3883.8616515837) (10 1248.1147058824 3842.3826923077))
((0 . "LWPOLYLINE") (100 . "AcDbEntity") (8 . "PLANTS") (62 . 94) (370 . 13) (100 . "AcDbPolyline") (90 . 3) (70 . 0)
(43 . 0.0) (10 1248.1147058824 3883.8616515837) (10 1274.5130090498 3884.0125565611) (10 1287.7074660633
3889.517760181))
((0 . "LWPOLYLINE") (100 . "AcDbEntity") (8 . "PLANTS") (62 . 94) (370 . 13) (100 . "AcDbPolyline") (90 . 2) (70 . 0)
(43 . 0.0) (10 1285.8219457014 3842.3826923077) (10 1248.1147058824 3842.3826923077))
((0 . "LWPOLYLINE") (100 . "AcDbEntity") (8 . "PLANTS") (62 . 94) (370 . 13) (100 . "AcDbPolyline") (90 . 3) (70 . 0)
(43 . 0.0) (10 1248.1147058824 3793.3639140271) (10 1244.3438914027 3812.2171945701) (10 1248.1147058824
3842.3826923077))
((0 . "LWPOLYLINE") (100 . "AcDbEntity") (8 . "PLANTS") (62 . 94) (370 . 13) (100 . "AcDbPolyline") (90 . 2) (70 . 0)
(43 . 0.0) (10 1248.1147058824 3793.3639140271) (10 1248.1147058824 3774.5093891403))
((0 . "LWPOLYLINE") (100 . "AcDbEntity") (8 . "PLANTS") (62 . 94) (370 . 13) (100 . "AcDbPolyline") (90 . 2) (70 . 0)
(43 . 0.0) (10 1248.1147058824 3793.3639140271) (10 1259.4269230769 3797.1338235294))
((0 . "LWPOLYLINE") (100 . "AcDbEntity") (8 . "PLANTS") (62 . 94) (370 . 13) (100 . "AcDbPolyline") (90 . 3) (70 . 0)
(43 . 0.0) (10 1248.1147058824 3774.5093891403) (10 1255.6627828054 3768.1593891403) (10 1289.592760181
3755.6561085973))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1248.1147058824 1217.9496606336 0.0) (10 1266.9749473511 1225.0480392535 0.0) (10 1294.7435881151
1211.8192455713 0.0) (10 1308.4463800905 1234.9179864253 0.0))
((0 . "LWPOLYLINE") (100 . "AcDbEntity") (8 . "PLANTS") (62 . 94) (370 . 13) (100 . "AcDbPolyline") (90 . 2) (70 . 0)
(43 . 0.0) (10 1248.1147058824 923.8320135747) (10 1248.8003374923 916.2895927602))
((0 . "LWPOLYLINE") (100 . "AcDbEntity") (8 . "PLANTS") (62 . 94) (370 . 13) (100 . "AcDbPolyline") (90 . 3) (70 . 0)
(43 . 0.0) (10 1248.1147058824 923.8320135747) (10 1248.2626696833 972.850678733) (10 1255.6561085973 995.4751131222))
((0 . "LWPOLYLINE") (100 . "AcDbEntity") (8 . "PLANTS") (62 . 94) (370 . 13) (100 . "AcDbPolyline") (90 . 2) (70 . 0)
(43 . 0.0) (10 1251.8852941176 1108.5972850679) (10 1270.7391402715 1108.5972850679))
((0 . "LWPOLYLINE") (100 . "AcDbEntity") (8 . "PLANTS") (62 . 94) (370 . 13) (100 . "AcDbPolyline") (90 . 2) (70 . 0)
(43 . 0.0) (10 1266.9683257919 3959.2760180995) (10 1255.6561085973 3959.2760180995))
((0 . "LWPOLYLINE") (100 . "AcDbEntity") (8 . "PLANTS") (62 . 94) (370 . 13) (100 . "AcDbPolyline") (90 . 3) (70 . 0)
(43 . 0.0) (10 1255.6561085973 3959.2760180995) (10 1252.9416289593 3981.9004524887) (10 1282.0513574661
4034.6903846154))
((0 . "LWPOLYLINE") (100 . "AcDbEntity") (8 . "PLANTS") (62 . 94) (370 . 13) (100 . "AcDbPolyline") (90 . 2) (70 . 0)
(43 . 0.0) (10 1293.3635746606 976.6204751131) (10 1255.6561085973 995.4751131222))
((0 . "LWPOLYLINE") (100 . "AcDbEntity") (8 . "PLANTS") (62 . 94) (370 . 13) (100 . "AcDbPolyline") (90 . 3) (70 . 0)
(43 . 0.0) (10 1266.9683257919 3959.2760180995) (10 1268.0245475113 3944.1926470588) (10 1287.7074660633
3889.517760181))
((0 . "LWPOLYLINE") (100 . "AcDbEntity") (8 . "PLANTS") (62 . 94) (370 . 13) (100 . "AcDbPolyline") (90 . 3) (70 . 0)
(43 . 0.0) (10 1297.1341628959 3963.0471719457) (10 1274.5164027149 3962.8987556561) (10 1266.9683257919
3959.2760180995))
((0 . "LWPOLYLINE") (100 . "AcDbEntity") (8 . "PLANTS") (62 . 94) (370 . 13) (100 . "AcDbPolyline") (90 . 2) (70 . 0)
(43 . 0.0) (10 2065.9107934546 505.902801703) (10 2220.9650452489 505.2790723982))
((0 . "LWPOLYLINE") (100 . "AcDbEntity") (8 . "PLANTS") (62 . 94) (370 . 13) (100 . "AcDbPolyline") (90 . 3) (70 . 0)
(43 . 0.0) (10 1353.6952488688 1052.036199095) (10 1285.8219457014 1094.5709276018) (10 1270.7391402715
1108.5972850679))
((0 . "LWPOLYLINE") (100 . "AcDbEntity") (8 . "PLANTS") (62 . 94) (370 . 13) (100 . "AcDbPolyline") (90 . 3) (70 . 0)
(43 . 0.0) (10 1270.7391402715 1108.5972850679) (10 1278.2872171946 1119.7617647059) (10 1293.3635746606
1127.4519230769))
((0 . "LWPOLYLINE") (100 . "AcDbEntity") (8 . "PLANTS") (62 . 94) (370 . 13) (100 . "AcDbPolyline") (90 . 3) (70 . 0)
(43 . 0.0) (10 1304.6757918552 1003.0175339367) (10 1283.2489819005 1033.181561086) (10 1270.7391402715
1063.3484162896))
((0 . "LWPOLYLINE") (100 . "AcDbEntity") (8 . "PLANTS") (62 . 94) (370 . 13) (100 . "AcDbPolyline") (90 . 2) (70 . 0)
(43 . 0.0) (10 1327.3002262443 4032.8054298643) (10 1282.0513574661 4034.6903846154))
((0 . "LWPOLYLINE") (100 . "AcDbEntity") (8 . "PLANTS") (62 . 94) (370 . 13) (100 . "AcDbPolyline") (90 . 3) (70 . 0)
(43 . 0.0) (10 1280.6037517807 4061.2242378807) (10 1278.5766968326 4042.2389140271) (10 1282.0513574661
4034.6903846154))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1285.8219457013 3842.3826923077 0.0) (10 1300.2051870661 3797.9764292732 0.0) (10 1357.4006737093
3811.0594642536 0.0) (10 1383.8613122172 3834.8416289593 0.0))
((0 . "LWPOLYLINE") (100 . "AcDbEntity") (8 . "PLANTS") (62 . 94) (370 . 13) (100 . "AcDbPolyline") (90 . 2) (70 . 0)
(43 . 0.0) (10 1285.8219457014 3842.3826923077) (10 1287.7074660633 3889.517760181))
((0 . "LWPOLYLINE") (100 . "AcDbEntity") (8 . "PLANTS") (62 . 94) (370 . 13) (100 . "AcDbPolyline") (90 . 2) (70 . 0)
(43 . 0.0) (10 1349.9246606335 3891.4027149321) (10 1287.7074660633 3889.517760181))
((0 . "LWPOLYLINE") (100 . "AcDbEntity") (8 . "PLANTS") (62 . 94) (370 . 13) (100 . "AcDbPolyline") (90 . 2) (70 . 0)
(43 . 0.0) (10 1290.3800688467 3744.3438914027) (10 1289.592760181 3755.6561085973))
((0 . "LWPOLYLINE") (100 . "AcDbEntity") (8 . "PLANTS") (62 . 94) (370 . 13) (100 . "AcDbPolyline") (90 . 3) (70 . 0)
(43 . 0.0) (10 1289.592760181 3755.6561085973) (10 1308.4463800905 3763.049321267) (10 1421.5685520362 3763.1971719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1342.3830316742 1131.221719457 0.0) (10 1331.6587049797 1120.3891618745 0.0) (10 1303.4485113562
1109.3955268738 0.0) (10 1293.3635746606 1127.4519230769 0.0))
((0 . "LWPOLYLINE") (100 . "AcDbEntity") (8 . "PLANTS") (62 . 94) (370 . 13) (100 . "AcDbPolyline") (90 . 3) (70 . 0)
(43 . 0.0) (10 1293.3635746606 1127.4519230769) (10 1301.0530542986 1146.2988687783) (10 1319.7585972851
1157.6159502262))
((0 . "LWPOLYLINE") (100 . "AcDbEntity") (8 . "PLANTS") (62 . 94) (370 . 13) (100 . "AcDbPolyline") (90 . 2) (70 . 0)
(43 . 0.0) (10 1300.9049773756 931.3716063348) (10 1293.3635746606 976.6204751131))
((0 . "LWPOLYLINE") (100 . "AcDbEntity") (8 . "PLANTS") (62 . 94) (370 . 13) (100 . "AcDbPolyline") (90 . 3) (70 . 0)
(43 . 0.0) (10 1304.6757918552 1003.0175339367) (10 1303.4714932127 991.7053167421) (10 1293.3635746606 976.6204751131))
((0 . "LWPOLYLINE") (100 . "AcDbEntity") (8 . "PLANTS") (62 . 94) (370 . 13) (100 . "AcDbPolyline") (90 . 2) (70 . 0)
(43 . 0.0) (10 1300.9049773756 931.3716063348) (10 1303.1797484162 916.2895927602))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1297.1341628959 3963.0471719457 0.0) (10 1308.4895788116 3934.6024829274 0.0) (10 1344.6950275588
3940.3504235981 0.0) (10 1361.2368778281 3917.7983031674 0.0))
((0 . "LWPOLYLINE") (100 . "AcDbEntity") (8 . "PLANTS") (62 . 94) (370 . 13) (100 . "AcDbPolyline") (90 . 3) (70 . 0)
(43 . 0.0) (10 1297.1341628959 3963.0471719457) (10 1304.6757918552 3974.3593891403) (10 1308.4463800905
3974.3593891403))
((0 . "LWPOLYLINE") (100 . "AcDbEntity") (8 . "PLANTS") (62 . 94) (370 . 13) (100 . "AcDbPolyline") (90 . 3) (70 . 0)
(43 . 0.0) (10 1372.5490950226 935.1442307692) (10 1365.0009049774 931.5200226244) (10 1300.9049773756 931.3716063348))
((0 . "LWPOLYLINE") (100 . "AcDbEntity") (8 . "PLANTS") (62 . 94) (370 . 13) (100 . "AcDbPolyline") (90 . 2) (70 . 0)
(43 . 0.0) (10 1308.4463800905 1234.9179864253) (10 1306.600097299 1241.3793115071))
((0 . "LWPOLYLINE") (100 . "AcDbEntity") (8 . "PLANTS") (62 . 94) (370 . 13) (100 . "AcDbPolyline") (90 . 2) (70 . 0)
(43 . 0.0) (10 1334.8416289593 1003.0175339367) (10 1304.6757918552 1003.0175339367))
((0 . "LWPOLYLINE") (100 . "AcDbEntity") (8 . "PLANTS") (62 . 94) (370 . 13) (100 . "AcDbPolyline") (90 . 2) (70 . 0)
(43 . 0.0) (10 1331.0708144796 4053.5449095023) (10 1326.9877337568 4075.8718111364))
((0 . "LWPOLYLINE") (100 . "AcDbEntity") (8 . "PLANTS") (62 . 94) (370 . 13) (100 . "AcDbPolyline") (90 . 3) (70 . 0)
(43 . 0.0) (10 1308.4463800905 3974.3593891403) (10 1323.5294117647 3970.7363122172) (10 1372.5490950226
3970.5882352941))
((0 . "LWPOLYLINE") (100 . "AcDbEntity") (8 . "PLANTS") (62 . 94) (370 . 13) (100 . "AcDbPolyline") (90 . 3) (70 . 0)
(43 . 0.0) (10 1308.4463800905 3974.3593891403) (10 1309.6441176471 3996.9838235294) (10 1327.3002262443
4032.8054298643))
((0 . "LWPOLYLINE") (100 . "AcDbEntity") (8 . "PLANTS") (62 . 94) (370 . 13) (100 . "AcDbPolyline") (90 . 3) (70 . 0)
(43 . 0.0) (10 1334.8416289593 1176.4705882353) (10 1317.0376696833 1206.6374434389) (10 1308.4463800905
1234.9179864253))
((0 . "LWPOLYLINE") (100 . "AcDbEntity") (8 . "PLANTS") (62 . 94) (370 . 13) (100 . "AcDbPolyline") (90 . 2) (70 . 0)
(43 . 0.0) (10 1308.4463800905 1234.9179864253) (10 1368.778280543 1240.5740950226))
((0 . "LWPOLYLINE") (100 . "AcDbEntity") (8 . "PLANTS") (62 . 94) (370 . 13) (100 . "AcDbPolyline") (90 . 2) (70 . 0)
(43 . 0.0) (10 1342.3830316742 1131.221719457) (10 1319.7585972851 1157.6159502262))
((0 . "LWPOLYLINE") (100 . "AcDbEntity") (8 . "PLANTS") (62 . 94) (370 . 13) (100 . "AcDbPolyline") (90 . 2) (70 . 0)
(43 . 0.0) (10 1334.8416289593 1176.4705882353) (10 1319.7585972851 1157.6159502262))
((0 . "LWPOLYLINE") (100 . "AcDbEntity") (8 . "PLANTS") (62 . 94) (370 . 13) (100 . "AcDbPolyline") (90 . 3) (70 . 0)
(43 . 0.0) (10 1370.6635746606 4044.1176470588) (10 1353.695361991 4031.0744343891) (10 1327.3002262443
4032.8054298643))
((0 . "LWPOLYLINE") (100 . "AcDbEntity") (8 . "PLANTS") (62 . 94) (370 . 13) (100 . "AcDbPolyline") (90 . 2) (70 . 0)
(43 . 0.0) (10 1331.0708144796 4053.5449095023) (10 1327.3002262443 4032.8054298643))
((0 . "LWPOLYLINE") (100 . "AcDbEntity") (8 . "PLANTS") (62 . 94) (370 . 13) (100 . "AcDbPolyline") (90 . 2) (70 . 0)
(43 . 0.0) (10 1331.0708144796 4053.5449095023) (10 1361.2368778281 4057.3148190045))
((0 . "LWPOLYLINE") (100 . "AcDbEntity") (8 . "PLANTS") (62 . 94) (370 . 13) (100 . "AcDbPolyline") (90 . 2) (70 . 0)
(43 . 0.0) (10 1334.8416289593 1176.4705882353) (10 1342.3830316742 1176.4705882353))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1372.5490950226 935.1442307692 0.0) (10 1374.0211021945 962.3840718131 0.0) (10 1346.0088958056
982.1372760403 0.0) (10 1334.8416289593 1003.0175339367 0.0))
((0 . "LWPOLYLINE") (100 . "AcDbEntity") (8 . "PLANTS") (62 . 94) (370 . 13) (100 . "AcDbPolyline") (90 . 3) (70 . 0)
(43 . 0.0) (10 1353.6952488688 1021.8693438914) (10 1342.3895927602 1014.3221719457) (10 1334.8416289593
1003.0175339367))
((0 . "LWPOLYLINE") (100 . "AcDbEntity") (8 . "PLANTS") (62 . 94) (370 . 13) (100 . "AcDbPolyline") (90 . 3) (70 . 0)
(43 . 0.0) (10 1366.8929864253 1133.1080316742) (10 1354.7547511312 1146.3016968326) (10 1342.3830316742
1176.4705882353))
((0 . "LWPOLYLINE") (100 . "AcDbEntity") (8 . "PLANTS") (62 . 94) (370 . 13) (100 . "AcDbPolyline") (90 . 3) (70 . 0)
(43 . 0.0) (10 1383.8613122172 1214.1770361991) (10 1372.5424208145 1191.707918552) (10 1342.3830316742
1176.4705882353))
((0 . "LWPOLYLINE") (100 . "AcDbEntity") (8 . "PLANTS") (62 . 94) (370 . 13) (100 . "AcDbPolyline") (90 . 2) (70 . 0)
(43 . 0.0) (10 1342.3830316742 1131.221719457) (10 1366.8929864253 1133.1080316742))
((0 . "LWPOLYLINE") (100 . "AcDbEntity") (8 . "PLANTS") (62 . 94) (370 . 13) (100 . "AcDbPolyline") (90 . 3) (70 . 0)
(43 . 0.0) (10 1349.9246606335 3891.4027149321) (10 1357.4727375566 3881.1402714932) (10 1380.0904977376
3868.778280543))
((0 . "LWPOLYLINE") (100 . "AcDbEntity") (8 . "PLANTS") (62 . 94) (370 . 13) (100 . "AcDbPolyline") (90 . 2) (70 . 0)
(43 . 0.0) (10 1349.9246606335 3891.4027149321) (10 1361.2368778281 3917.7983031674))
((0 . "LWPOLYLINE") (100 . "AcDbEntity") (8 . "PLANTS") (62 . 94) (370 . 13) (100 . "AcDbPolyline") (90 . 2) (70 . 0)
(43 . 0.0) (10 1353.6952488688 1052.036199095) (10 1353.6952488688 1021.8693438914))
((0 . "LWPOLYLINE") (100 . "AcDbEntity") (8 . "PLANTS") (62 . 94) (370 . 13) (100 . "AcDbPolyline") (90 . 2) (70 . 0)
(43 . 0.0) (10 1353.6952488688 1052.036199095) (10 1398.9441176471 1055.8059954751))
((0 . "LWPOLYLINE") (100 . "AcDbEntity") (8 . "PLANTS") (62 . 94) (370 . 13) (100 . "AcDbPolyline") (90 . 3) (70 . 0)
(43 . 0.0) (10 1353.6952488688 1021.8693438914) (10 1383.8613122172 1018.2541855204) (10 1402.7149321267
1025.6419683258))
((0 . "LWPOLYLINE") (100 . "AcDbEntity") (8 . "PLANTS") (62 . 94) (370 . 13) (100 . "AcDbPolyline") (90 . 2) (70 . 0)
(43 . 0.0) (10 1370.6635746606 4044.1176470588) (10 1361.2368778281 4057.3148190045))
((0 . "LWPOLYLINE") (100 . "AcDbEntity") (8 . "PLANTS") (62 . 94) (370 . 13) (100 . "AcDbPolyline") (90 . 2) (70 . 0)
(43 . 0.0) (10 1365.3216033899 4087.9772436521) (10 1361.2368778281 4057.3148190045))
((0 . "LWPOLYLINE") (100 . "AcDbEntity") (8 . "PLANTS") (62 . 94) (370 . 13) (100 . "AcDbPolyline") (90 . 2) (70 . 0)
(43 . 0.0) (10 1361.2368778281 3917.7983031674) (10 1410.2563348416 3917.7983031674))
((0 . "LWPOLYLINE") (100 . "AcDbEntity") (8 . "PLANTS") (62 . 94) (370 . 13) (100 . "AcDbPolyline") (90 . 3) (70 . 0)
(43 . 0.0) (10 1398.9441176471 1097.2850678733) (10 1380.2385746606 1108.6035067873) (10 1366.8929864253
1133.1080316742))
((0 . "LWPOLYLINE") (100 . "AcDbEntity") (8 . "PLANTS") (62 . 94) (370 . 13) (100 . "AcDbPolyline") (90 . 3) (70 . 0)
(43 . 0.0) (10 1398.9441176471 1165.1583710407) (10 1383.854638009 1146.3037330317) (10 1366.8929864253
1133.1080316742))
((0 . "LWPOLYLINE") (100 . "AcDbEntity") (8 . "PLANTS") (62 . 94) (370 . 13) (100 . "AcDbPolyline") (90 . 2) (70 . 0)
(43 . 0.0) (10 1368.778280543 1240.5740950226) (10 1368.778280543 1261.0145272684))
((0 . "LWPOLYLINE") (100 . "AcDbEntity") (8 . "PLANTS") (62 . 94) (370 . 13) (100 . "AcDbPolyline") (90 . 3) (70 . 0)
(43 . 0.0) (10 1368.778280543 1240.5740950226) (10 1375.2701357466 1236.6481900452) (10 1383.8613122172
1214.1770361991))
((0 . "LWPOLYLINE") (100 . "AcDbEntity") (8 . "PLANTS") (62 . 94) (370 . 13) (100 . "AcDbPolyline") (90 . 3) (70 . 0)
(43 . 0.0) (10 2077.6774886878 629.7143665158) (10 2058.8235294118 633.4841628959) (10 2031.0582324456 633.3324778924))
((0 . "LWPOLYLINE") (100 . "AcDbEntity") (8 . "PLANTS") (62 . 94) (370 . 13) (100 . "AcDbPolyline") (90 . 3) (70 . 0)
(43 . 0.0) (10 1395.1735294118 4004.5248868778) (10 1382.8018099548 4030.9229638009) (10 1370.6635746606
4044.1176470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1414.0271493213 4046.00260181 0.0) (10 1402.3128284973 4057.6110588834 0.0) (10 1382.1140705401
4054.9292129617 0.0) (10 1370.6635746606 4044.1176470588 0.0))
((0 . "LWPOLYLINE") (100 . "AcDbEntity") (8 . "PLANTS") (62 . 94) (370 . 13) (100 . "AcDbPolyline") (90 . 3) (70 . 0)
(43 . 0.0) (10 1372.5490950226 3970.5882352941) (10 1391.2547511312 3955.4986425339) (10 1414.0271493213
3925.3393665158))
((0 . "LWPOLYLINE") (100 . "AcDbEntity") (8 . "PLANTS") (62 . 94) (370 . 13) (100 . "AcDbPolyline") (90 . 3) (70 . 0)
(43 . 0.0) (10 1395.1735294118 4004.5248868778) (10 1381.1466063348 3989.2936651584) (10 1372.5490950226
3970.5882352941))
((0 . "LWPOLYLINE") (100 . "AcDbEntity") (8 . "PLANTS") (62 . 94) (370 . 13) (100 . "AcDbPolyline") (90 . 2) (70 . 0)
(43 . 0.0) (10 1372.5490950226 935.1442307692) (10 1440.4222850679 935.1433257919))
((0 . "LWPOLYLINE") (100 . "AcDbEntity") (8 . "PLANTS") (62 . 94) (370 . 13) (100 . "AcDbPolyline") (90 . 3) (70 . 0)
(43 . 0.0) (10 2047.7287074074 572.381053813) (10 2081.4479638009 573.1463800905) (10 2092.7601809955 569.3806561086))
((0 . "LWPOLYLINE") (100 . "AcDbEntity") (8 . "PLANTS") (62 . 94) (370 . 13) (100 . "AcDbPolyline") (90 . 2) (70 . 0)
(43 . 0.0) (10 1380.0904977376 3868.778280543) (10 1383.8613122172 3834.8416289593))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1380.0904977376 3868.778280543 0.0) (10 1399.0930628553 3876.9024910756 0.0) (10 1406.1105718178
3899.7292649009 0.0) (10 1410.2563348416 3917.7983031674 0.0))
((0 . "LWPOLYLINE") (100 . "AcDbEntity") (8 . "PLANTS") (62 . 94) (370 . 13) (100 . "AcDbPolyline") (90 . 2) (70 . 0)
(43 . 0.0) (10 1398.9441176471 3834.8416289593) (10 1383.8613122172 3834.8416289593))
((0 . "LWPOLYLINE") (100 . "AcDbEntity") (8 . "PLANTS") (62 . 94) (370 . 13) (100 . "AcDbPolyline") (90 . 3) (70 . 0)
(43 . 0.0) (10 1451.7345022624 1210.407239819) (10 1417.7979638009 1206.7845022624) (10 1383.8613122172
1214.1770361991))
((0 . "LWPOLYLINE") (100 . "AcDbEntity") (8 . "PLANTS") (62 . 94) (370 . 13) (100 . "AcDbPolyline") (90 . 2) (70 . 0)
(43 . 0.0) (10 1395.1735294118 4004.5248868778) (10 1417.7979638009 4004.5248868778))
((0 . "LWPOLYLINE") (100 . "AcDbEntity") (8 . "PLANTS") (62 . 94) (370 . 13) (100 . "AcDbPolyline") (90 . 2) (70 . 0)
(43 . 0.0) (10 1398.9441176471 1165.1583710407) (10 1395.1735294118 1176.4705882353))
((0 . "LWPOLYLINE") (100 . "AcDbEntity") (8 . "PLANTS") (62 . 94) (370 . 13) (100 . "AcDbPolyline") (90 . 2) (70 . 0)
(43 . 0.0) (10 1398.9441176471 3834.8416289593) (10 1421.5685520362 3763.1971719457))
((0 . "LWPOLYLINE") (100 . "AcDbEntity") (8 . "PLANTS") (62 . 94) (370 . 13) (100 . "AcDbPolyline") (90 . 2) (70 . 0)
(43 . 0.0) (10 1463.046719457 3855.5811085973) (10 1398.9441176471 3834.8416289593))
((0 . "LWPOLYLINE") (100 . "AcDbEntity") (8 . "PLANTS") (62 . 94) (370 . 13) (100 . "AcDbPolyline") (90 . 3) (70 . 0)
(43 . 0.0) (10 1398.9441176471 1165.1583710407) (10 1414.0271493213 1161.5356334842) (10 1455.5053167421
1161.3885746606))
((0 . "LWPOLYLINE") (100 . "AcDbEntity") (8 . "PLANTS") (62 . 94) (370 . 13) (100 . "AcDbPolyline") (90 . 2) (70 . 0)
(43 . 0.0) (10 1398.9441176471 1097.2850678733) (10 1398.9441176471 1055.8059954751))
((0 . "LWPOLYLINE") (100 . "AcDbEntity") (8 . "PLANTS") (62 . 94) (370 . 13) (100 . "AcDbPolyline") (90 . 3) (70 . 0)
(43 . 0.0) (10 1398.9441176471 1097.2850678733) (10 1432.8807692308 1111.3114253394) (10 1455.5053167421
1112.367081448))
((0 . "LWPOLYLINE") (100 . "AcDbEntity") (8 . "PLANTS") (62 . 94) (370 . 13) (100 . "AcDbPolyline") (90 . 3) (70 . 0)
(43 . 0.0) (10 1402.7149321267 1052.036199095) (10 1402.7149321267 1055.8059954751) (10 1398.9441176471
1055.8059954751))
((0 . "LWPOLYLINE") (100 . "AcDbEntity") (8 . "PLANTS") (62 . 94) (370 . 13) (100 . "AcDbPolyline") (90 . 2) (70 . 0)
(43 . 0.0) (10 1402.7149321267 1052.036199095) (10 1398.9441176471 1055.8059954751))
((0 . "LWPOLYLINE") (100 . "AcDbEntity") (8 . "PLANTS") (62 . 94) (370 . 13) (100 . "AcDbPolyline") (90 . 2) (70 . 0)
(43 . 0.0) (10 1402.7149321267 1052.036199095) (10 1402.7149321267 1033.181561086))
((0 . "LWPOLYLINE") (100 . "AcDbEntity") (8 . "PLANTS") (62 . 94) (370 . 13) (100 . "AcDbPolyline") (90 . 3) (70 . 0)
(43 . 0.0) (10 1444.1930995475 1048.2664027149) (10 1429.1101809955 1055.6527149321) (10 1402.7149321267
1052.036199095))
((0 . "LWPOLYLINE") (100 . "AcDbEntity") (8 . "PLANTS") (62 . 94) (370 . 13) (100 . "AcDbPolyline") (90 . 3) (70 . 0)
(43 . 0.0) (10 1402.7149321267 1033.181561086) (10 1406.4857466063 1033.181561086) (10 1410.2563348416 1025.6419683258))
((0 . "LWPOLYLINE") (100 . "AcDbEntity") (8 . "PLANTS") (62 . 94) (370 . 13) (100 . "AcDbPolyline") (90 . 2) (70 . 0)
(43 . 0.0) (10 1402.7149321267 1025.6419683258) (10 1402.7149321267 1033.181561086))
((0 . "LWPOLYLINE") (100 . "AcDbEntity") (8 . "PLANTS") (62 . 94) (370 . 13) (100 . "AcDbPolyline") (90 . 2) (70 . 0)
(43 . 0.0) (10 1402.7149321267 1025.6419683258) (10 1410.2563348416 1025.6419683258))
((0 . "LWPOLYLINE") (100 . "AcDbEntity") (8 . "PLANTS") (62 . 94) (370 . 13) (100 . "AcDbPolyline") (90 . 2) (70 . 0)
(43 . 0.0) (10 1414.0271493213 3925.3393665158) (10 1410.2563348416 3917.7983031674))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1504.5248868778 1033.181561086 0.0) (10 1472.6644017225 1035.1607970132 0.0) (10 1437.5449896297
987.8362526112 0.0) (10 1410.2563348416 1025.6419683259 0.0))
((0 . "LWPOLYLINE") (100 . "AcDbEntity") (8 . "PLANTS") (62 . 94) (370 . 13) (100 . "AcDbPolyline") (90 . 3) (70 . 0)
(43 . 0.0) (10 1414.0271493213 3925.3393665158) (10 1432.8807692308 3932.7325791855) (10 1474.3589366516
3932.8804298643))
((0 . "LWPOLYLINE") (100 . "AcDbEntity") (8 . "PLANTS") (62 . 94) (370 . 13) (100 . "AcDbPolyline") (90 . 3) (70 . 0)
(43 . 0.0) (10 2073.9062217195 754.1487556561) (10 2043.7408371041 750.3830316742) (10 2017.9462517383 750.4399767802))
((0 . "LWPOLYLINE") (100 . "AcDbEntity") (8 . "PLANTS") (62 . 94) (370 . 13) (100 . "AcDbPolyline") (90 . 3) (70 . 0)
(43 . 0.0) (10 1417.7979638009 4030.9204751131) (10 1421.7233031674 4020.0584841629) (10 1417.7979638009
4004.5248868778))
((0 . "LWPOLYLINE") (100 . "AcDbEntity") (8 . "PLANTS") (62 . 94) (370 . 13) (100 . "AcDbPolyline") (90 . 3) (70 . 0)
(43 . 0.0) (10 1417.7979638009 4004.5248868778) (10 1432.8807692308 3990.6462669683) (10 1447.963800905
3989.4415158371))
((0 . "LWPOLYLINE") (100 . "AcDbEntity") (8 . "PLANTS") (62 . 94) (370 . 13) (100 . "AcDbPolyline") (90 . 2) (70 . 0)
(43 . 0.0) (10 1436.6515837104 3755.6561085973) (10 1421.5685520362 3763.1971719457))
((0 . "LWPOLYLINE") (100 . "AcDbEntity") (8 . "PLANTS") (62 . 94) (370 . 13) (100 . "AcDbPolyline") (90 . 3) (70 . 0)
(43 . 0.0) (10 1421.5685520362 1255.6561085973) (10 1425.4940045249 1245.5487556561) (10 1451.7345022624
1236.8014705882))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2043.7408371041 855.9587104072 0.0) (10 2032.0975347143 841.4317754667 0.0) (10 2020.0521464862
859.4570725167 0.0) (10 2008.5605403364 855.2959713479 0.0))
((0 . "LWPOLYLINE") (100 . "AcDbEntity") (8 . "PLANTS") (62 . 94) (370 . 13) (100 . "AcDbPolyline") (90 . 3) (70 . 0)
(43 . 0.0) (10 2081.4479638009 693.8150452489) (10 2070.1357466063 690.0514705882) (10 2023.3516971333 690.0510165077))
((0 . "LWPOLYLINE") (100 . "AcDbEntity") (8 . "PLANTS") (62 . 94) (370 . 13) (100 . "AcDbPolyline") (90 . 3) (70 . 0)
(43 . 0.0) (10 2036.1990950226 814.479638009) (10 2017.3451357466 806.9441176471) (10 2012.8895982351 806.9322776361))
((0 . "LWPOLYLINE") (100 . "AcDbEntity") (8 . "PLANTS") (62 . 94) (370 . 13) (100 . "AcDbPolyline") (90 . 2) (70 . 0)
(43 . 0.0) (10 1436.6515837104 3755.6561085973) (10 1432.8874434389 3744.3438914027))
((0 . "LWPOLYLINE") (100 . "AcDbEntity") (8 . "PLANTS") (62 . 94) (370 . 13) (100 . "AcDbPolyline") (90 . 3) (70 . 0)
(43 . 0.0) (10 1436.6515837104 3755.6561085973) (10 1481.9004524887 3764.8693438914) (10 1523.3786199095
3763.1971719457))
((0 . "LWPOLYLINE") (100 . "AcDbEntity") (8 . "PLANTS") (62 . 94) (370 . 13) (100 . "AcDbPolyline") (90 . 3) (70 . 0)
(43 . 0.0) (10 2104.07239819 931.3716063348) (10 2088.9897058824 935.1433257919) (10 1440.4222850679 935.1433257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1440.4222850679 935.1433257919 0.0) (10 1430.9035697991 952.1111787771 0.0) (10 1447.176513833
978.9547314239 0.0) (10 1466.8175339367 969.0808823529 0.0))
((0 . "LWPOLYLINE") (100 . "AcDbEntity") (8 . "PLANTS") (62 . 94) (370 . 13) (100 . "AcDbPolyline") (90 . 2) (70 . 0)
(43 . 0.0) (10 1478.1297511312 3974.3593891403) (10 1447.963800905 3989.4415158371))
((0 . "LWPOLYLINE") (100 . "AcDbEntity") (8 . "PLANTS") (62 . 94) (370 . 13) (100 . "AcDbPolyline") (90 . 2) (70 . 0)
(43 . 0.0) (10 1451.7345022624 4034.6903846154) (10 1447.963800905 3989.4415158371))
((0 . "LWPOLYLINE") (100 . "AcDbEntity") (8 . "PLANTS") (62 . 94) (370 . 13) (100 . "AcDbPolyline") (90 . 3) (70 . 0)
(43 . 0.0) (10 1447.9845707683 4114.0813386136) (10 1448.1118778281 4046.003280543) (10 1451.7345022624
4034.6903846154))
((0 . "LWPOLYLINE") (100 . "AcDbEntity") (8 . "PLANTS") (62 . 94) (370 . 13) (100 . "AcDbPolyline") (90 . 3) (70 . 0)
(43 . 0.0) (10 1485.6711538462 4053.5449095023) (10 1466.8109728507 4035.8951357466) (10 1451.7345022624
4034.6903846154))
((0 . "LWPOLYLINE") (100 . "AcDbEntity") (8 . "PLANTS") (62 . 94) (370 . 13) (100 . "AcDbPolyline") (90 . 2) (70 . 0)
(43 . 0.0) (10 1451.7345022624 1210.407239819) (10 1451.7345022624 1236.8014705882))
((0 . "LWPOLYLINE") (100 . "AcDbEntity") (8 . "PLANTS") (62 . 94) (370 . 13) (100 . "AcDbPolyline") (90 . 2) (70 . 0)
(43 . 0.0) (10 2262.443438914 1349.9236425339) (10 2258.6202384578 1369.056576615))
((0 . "LWPOLYLINE") (100 . "AcDbEntity") (8 . "PLANTS") (62 . 94) (370 . 13) (100 . "AcDbPolyline") (90 . 3) (70 . 0)
(43 . 0.0) (10 1453.0460440076 1287.6253999414) (10 1455.5053167421 1255.6561085973) (10 1451.7345022624
1236.8014705882))
((0 . "LWPOLYLINE") (100 . "AcDbEntity") (8 . "PLANTS") (62 . 94) (370 . 13) (100 . "AcDbPolyline") (90 . 2) (70 . 0)
(43 . 0.0) (10 1451.7345022624 1210.407239819) (10 1455.5053167421 1195.3252262443))
((0 . "LWPOLYLINE") (100 . "AcDbEntity") (8 . "PLANTS") (62 . 94) (370 . 13) (100 . "AcDbPolyline") (90 . 2) (70 . 0)
(43 . 0.0) (10 1455.5053167421 1195.3252262443) (10 1489.4419683258 1195.3252262443))
((0 . "LWPOLYLINE") (100 . "AcDbEntity") (8 . "PLANTS") (62 . 94) (370 . 13) (100 . "AcDbPolyline") (90 . 2) (70 . 0)
(43 . 0.0) (10 1455.5053167421 1161.3885746606) (10 1455.5053167421 1195.3252262443))
((0 . "LWPOLYLINE") (100 . "AcDbEntity") (8 . "PLANTS") (62 . 94) (370 . 13) (100 . "AcDbPolyline") (90 . 2) (70 . 0)
(43 . 0.0) (10 1485.6711538462 1161.3885746606) (10 1455.5053167421 1161.3885746606))
((0 . "LWPOLYLINE") (100 . "AcDbEntity") (8 . "PLANTS") (62 . 94) (370 . 13) (100 . "AcDbPolyline") (90 . 2) (70 . 0)
(43 . 0.0) (10 1455.5053167421 1161.3885746606) (10 1455.5053167421 1112.367081448))
((0 . "LWPOLYLINE") (100 . "AcDbEntity") (8 . "PLANTS") (62 . 94) (370 . 13) (100 . "AcDbPolyline") (90 . 2) (70 . 0)
(43 . 0.0) (10 1463.046719457 1112.367081448) (10 1455.5053167421 1112.367081448))
((0 . "LWPOLYLINE") (100 . "AcDbEntity") (8 . "PLANTS") (62 . 94) (370 . 13) (100 . "AcDbPolyline") (90 . 3) (70 . 0)
(43 . 0.0) (10 1463.046719457 1112.367081448) (10 1463.046719457 1101.0548642534) (10 1459.2760180995 1097.2850678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1523.3786199095 3763.1971719457 0.0) (10 1531.655668373 3810.2969417364 0.0) (10 1462.429249537
3810.0264563 0.0) (10 1463.046719457 3855.5811085973 0.0))
((0 . "LWPOLYLINE") (100 . "AcDbEntity") (8 . "PLANTS") (62 . 94) (370 . 13) (100 . "AcDbPolyline") (90 . 2) (70 . 0)
(43 . 0.0) (10 1463.046719457 3855.5811085973) (10 1466.8175339367 3883.8616515837))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1463.046719457 3855.5811085973 0.0) (10 1485.5270320264 3873.5059516395 0.0) (10 1524.3763100603
3846.6474127797 0.0) (10 1530.9200226244 3891.4027149321 0.0))
((0 . "LWPOLYLINE") (100 . "AcDbEntity") (8 . "PLANTS") (62 . 94) (370 . 13) (100 . "AcDbPolyline") (90 . 3) (70 . 0)
(43 . 0.0) (10 1496.9833710407 1131.221719457) (10 1489.4352941176 1117.3430995475) (10 1463.046719457 1112.367081448))
((0 . "LWPOLYLINE") (100 . "AcDbEntity") (8 . "PLANTS") (62 . 94) (370 . 13) (100 . "AcDbPolyline") (90 . 2) (70 . 0)
(43 . 0.0) (10 1519.6078054299 3917.7983031674) (10 1474.3589366516 3932.8804298643))
((0 . "LWPOLYLINE") (100 . "AcDbEntity") (8 . "PLANTS") (62 . 94) (370 . 13) (100 . "AcDbPolyline") (90 . 2) (70 . 0)
(43 . 0.0) (10 1478.1297511312 3974.3593891403) (10 1474.3589366516 3932.8804298643))
((0 . "LWPOLYLINE") (100 . "AcDbEntity") (8 . "PLANTS") (62 . 94) (370 . 13) (100 . "AcDbPolyline") (90 . 3) (70 . 0)
(43 . 0.0) (10 1478.1297511312 3974.3593891403) (10 1493.2126696833 3974.507239819) (10 1512.0664027149
3981.9004524887))
((0 . "LWPOLYLINE") (100 . "AcDbEntity") (8 . "PLANTS") (62 . 94) (370 . 13) (100 . "AcDbPolyline") (90 . 2) (70 . 0)
(43 . 0.0) (10 1496.9833710407 1131.221719457) (10 1485.6711538462 1161.3885746606))
((0 . "LWPOLYLINE") (100 . "AcDbEntity") (8 . "PLANTS") (62 . 94) (370 . 13) (100 . "AcDbPolyline") (90 . 3) (70 . 0)
(43 . 0.0) (10 1485.6711538462 1161.3885746606) (10 1489.2938914027 1168.9357466063) (10 1489.4419683258
1195.3252262443))
((0 . "LWPOLYLINE") (100 . "AcDbEntity") (8 . "PLANTS") (62 . 94) (370 . 13) (100 . "AcDbPolyline") (90 . 2) (70 . 0)
(43 . 0.0) (10 1500.7541855204 1233.0316742081) (10 1489.4419683258 1195.3252262443))
((0 . "LWPOLYLINE") (100 . "AcDbEntity") (8 . "PLANTS") (62 . 94) (370 . 13) (100 . "AcDbPolyline") (90 . 2) (70 . 0)
(43 . 0.0) (10 1549.7737556561 1138.7641402715) (10 1496.9833710407 1131.221719457))
((0 . "LWPOLYLINE") (100 . "AcDbEntity") (8 . "PLANTS") (62 . 94) (370 . 13) (100 . "AcDbPolyline") (90 . 3) (70 . 0)
(43 . 0.0) (10 2005.4636129481 889.8944570136) (10 2028.6573529412 889.8944570136) (10 2047.5113122172 889.8944570136))
((0 . "LWPOLYLINE") (100 . "AcDbEntity") (8 . "PLANTS") (62 . 94) (370 . 13) (100 . "AcDbPolyline") (90 . 3) (70 . 0)
(43 . 0.0) (10 1508.2955882353 4101.3072021116) (10 1508.2955882353 4076.1693438914) (10 1508.2955882353
4064.8571266968))
((0 . "LWPOLYLINE") (100 . "AcDbEntity") (8 . "PLANTS") (62 . 94) (370 . 13) (100 . "AcDbPolyline") (90 . 2) (70 . 0)
(43 . 0.0) (10 1817.4307905484 4128.9101969837) (10 1817.4962669683 4074.2831447964))
((0 . "LWPOLYLINE") (100 . "AcDbEntity") (8 . "PLANTS") (62 . 94) (370 . 13) (100 . "AcDbPolyline") (90 . 3) (70 . 0)
(43 . 0.0) (10 1500.1610848566 1275.9644045953) (10 1496.9833710407 1259.4259049774) (10 1500.7541855204
1233.0316742081))
((0 . "LWPOLYLINE") (100 . "AcDbEntity") (8 . "PLANTS") (62 . 94) (370 . 13) (100 . "AcDbPolyline") (90 . 3) (70 . 0)
(43 . 0.0) (10 1549.7737556561 1248.1136877828) (10 1515.8371040724 1234.0811085973) (10 1500.7541855204
1233.0316742081))
((0 . "LWPOLYLINE") (100 . "AcDbEntity") (8 . "PLANTS") (62 . 94) (370 . 13) (100 . "AcDbPolyline") (90 . 3) (70 . 0)
(43 . 0.0) (10 1553.5444570136 1029.4117647059) (10 1512.0729638009 1029.5595022624) (10 1504.5248868778
1033.181561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1504.5248868778 1033.181561086 0.0) (10 1486.2949037406 1082.277643056 0.0) (10 1592.4116942472
1116.5342234319 0.0) (10 1553.5444570136 1036.9541855204 0.0))
((0 . "LWPOLYLINE") (100 . "AcDbEntity") (8 . "PLANTS") (62 . 94) (370 . 13) (100 . "AcDbPolyline") (90 . 3) (70 . 0)
(43 . 0.0) (10 1508.2955882353 4064.8571266968) (10 1508.4436651584 3993.2126696833) (10 1512.0664027149
3981.9004524887))
((0 . "LWPOLYLINE") (100 . "AcDbEntity") (8 . "PLANTS") (62 . 94) (370 . 13) (100 . "AcDbPolyline") (90 . 3) (70 . 0)
(43 . 0.0) (10 1572.3981900452 4053.5449095023) (10 1586.2833710407 4061.2406108597) (10 1591.0473277962
4073.7232889247))
((0 . "LWPOLYLINE") (100 . "AcDbEntity") (8 . "PLANTS") (62 . 94) (370 . 13) (100 . "AcDbPolyline") (90 . 3) (70 . 0)
(43 . 0.0) (10 1556.6355762258 4085.1938727814) (10 1534.6908371041 4069.8317873303) (10 1508.2955882353
4064.8571266968))
((0 . "LWPOLYLINE") (100 . "AcDbEntity") (8 . "PLANTS") (62 . 94) (370 . 13) (100 . "AcDbPolyline") (90 . 2) (70 . 0)
(43 . 0.0) (10 1519.6078054299 3981.9004524887) (10 1512.0664027149 3981.9004524887))
((0 . "LWPOLYLINE") (100 . "AcDbEntity") (8 . "PLANTS") (62 . 94) (370 . 13) (100 . "AcDbPolyline") (90 . 2) (70 . 0)
(43 . 0.0) (10 1519.6078054299 3981.9004524887) (10 1527.149321267 3981.9004524887))
((0 . "LWPOLYLINE") (100 . "AcDbEntity") (8 . "PLANTS") (62 . 94) (370 . 13) (100 . "AcDbPolyline") (90 . 3) (70 . 0)
(43 . 0.0) (10 1519.6078054299 3981.9004524887) (10 1519.6078054299 3978.1292986425) (10 1527.149321267
3974.3593891403))
((0 . "LWPOLYLINE") (100 . "AcDbEntity") (8 . "PLANTS") (62 . 94) (370 . 13) (100 . "AcDbPolyline") (90 . 3) (70 . 0)
(43 . 0.0) (10 1519.6078054299 3917.7983031674) (10 1520.8121040724 3910.2559954751) (10 1530.9200226244
3902.7149321267))
((0 . "LWPOLYLINE") (100 . "AcDbEntity") (8 . "PLANTS") (62 . 94) (370 . 13) (100 . "AcDbPolyline") (90 . 3) (70 . 0)
(43 . 0.0) (10 1519.6078054299 3917.7983031674) (10 1519.7558823529 3951.7349547511) (10 1527.149321267
3974.3593891403))
((0 . "LWPOLYLINE") (100 . "AcDbEntity") (8 . "PLANTS") (62 . 94) (370 . 13) (100 . "AcDbPolyline") (90 . 2) (70 . 0)
(43 . 0.0) (10 1523.3786199095 3763.1971719457) (10 1530.9200226244 3759.4272624434))
((0 . "LWPOLYLINE") (100 . "AcDbEntity") (8 . "PLANTS") (62 . 94) (370 . 13) (100 . "AcDbPolyline") (90 . 2) (70 . 0)
(43 . 0.0) (10 1527.149321267 3974.3593891403) (10 1527.149321267 3981.9004524887))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3221580611)
(40 . 0.5435381667) (40 . 1) (40 . 1) (40 . 1) (40 . 1) (10 1610.1055429864 4019.6082579186 0.0) (10 1598.8007359594
4023.0122591651 0.0) (10 1580.8992996873 4014.8974592941 0.0) (10 1541.7733582099 4030.5868755295 0.0) (10
1539.5368003698 3989.4051168957 0.0) (10 1527.149321267 3981.9004524887 0.0))
((0 . "LWPOLYLINE") (100 . "AcDbEntity") (8 . "PLANTS") (62 . 94) (370 . 13) (100 . "AcDbPolyline") (90 . 3) (70 . 0)
(43 . 0.0) (10 1572.3981900452 3966.817081448) (10 1549.7737556561 3974.2109728507) (10 1527.149321267 3974.3593891403))
((0 . "LWPOLYLINE") (100 . "AcDbEntity") (8 . "PLANTS") (62 . 94) (370 . 13) (100 . "AcDbPolyline") (90 . 2) (70 . 0)
(43 . 0.0) (10 1530.9200226244 3759.4272624434) (10 1529.4117171951 3744.3438914027))
((0 . "LWPOLYLINE") (100 . "AcDbEntity") (8 . "PLANTS") (62 . 94) (370 . 13) (100 . "AcDbPolyline") (90 . 3) (70 . 0)
(43 . 0.0) (10 2254.9019230769 4174.2081447964) (10 2254.9019230769 4193.0614253394) (10 2254.9019230769
4200.1320065045))
((0 . "LWPOLYLINE") (100 . "AcDbEntity") (8 . "PLANTS") (62 . 94) (370 . 13) (100 . "AcDbPolyline") (90 . 2) (70 . 0)
(43 . 0.0) (10 1530.9200226244 3902.7149321267) (10 1530.9200226244 3891.4027149321))
((0 . "LWPOLYLINE") (100 . "AcDbEntity") (8 . "PLANTS") (62 . 94) (370 . 13) (100 . "AcDbPolyline") (90 . 2) (70 . 0)
(43 . 0.0) (10 1530.9200226244 3902.7149321267) (10 1572.3981900452 3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1598.7933257919 3868.778280543 0.0) (10 1584.9583849949 3891.9965438133 0.0) (10 1548.4894304949
3871.077441908 0.0) (10 1530.9200226244 3891.4027149321 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.8022136381) (40
. 1) (40 . 1) (40 . 1) (40 . 1) (10 1934.3891402715 3763.1971719457 0.0) (10 1826.7602138131 3773.4079239042 0.0) (10
1690.7111426556 3764.0571917349 0.0) (10 1557.1944970688 3764.9495687176 0.0) (10 1530.9200226244 3759.4272624435 0.0))
((0 . "LWPOLYLINE") (100 . "AcDbEntity") (8 . "PLANTS") (62 . 94) (370 . 13) (100 . "AcDbPolyline") (90 . 3) (70 . 0)
(43 . 0.0) (10 1595.0226244344 3849.925) (10 1564.8566742081 3839.5076923077) (10 1534.6908371041 3819.7582579186))
((0 . "LWPOLYLINE") (100 . "AcDbEntity") (8 . "PLANTS") (62 . 94) (370 . 13) (100 . "AcDbPolyline") (90 . 3) (70 . 0)
(43 . 0.0) (10 1568.6274886878 1217.9496606335) (10 1548.7240950226 1191.7010180995) (10 1534.6908371041
1184.0130090498))
((0 . "LWPOLYLINE") (100 . "AcDbEntity") (8 . "PLANTS") (62 . 94) (370 . 13) (100 . "AcDbPolyline") (90 . 2) (70 . 0)
(43 . 0.0) (10 1549.7737556561 1248.1136877828) (10 1564.8566742081 1244.3438914027))
((0 . "LWPOLYLINE") (100 . "AcDbEntity") (8 . "PLANTS") (62 . 94) (370 . 13) (100 . "AcDbPolyline") (90 . 2) (70 . 0)
(43 . 0.0) (10 1551.8948538205 1258.7198149407) (10 1549.7737556561 1248.1136877828))
((0 . "LWPOLYLINE") (100 . "AcDbEntity") (8 . "PLANTS") (62 . 94) (370 . 13) (100 . "AcDbPolyline") (90 . 3) (70 . 0)
(43 . 0.0) (10 1549.7737556561 1138.7641402715) (10 1564.8566742081 1127.5996606335) (10 1617.6470588235
1119.9095022624))
((0 . "LWPOLYLINE") (100 . "AcDbEntity") (8 . "PLANTS") (62 . 94) (370 . 13) (100 . "AcDbPolyline") (90 . 3) (70 . 0)
(43 . 0.0) (10 1549.7737556561 1138.7641402715) (10 1568.6274886878 1160.3314479638) (10 1606.334841629
1172.7007918552))
((0 . "LWPOLYLINE") (100 . "AcDbEntity") (8 . "PLANTS") (62 . 94) (370 . 13) (100 . "AcDbPolyline") (90 . 2) (70 . 0)
(43 . 0.0) (10 1561.0859728507 1036.9541855204) (10 1553.5444570136 1036.9541855204))
((0 . "LWPOLYLINE") (100 . "AcDbEntity") (8 . "PLANTS") (62 . 94) (370 . 13) (100 . "AcDbPolyline") (90 . 2) (70 . 0)
(43 . 0.0) (10 1553.5444570136 1029.4117647059) (10 1553.5444570136 1036.9541855204))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1553.5444570136 1029.4117647059 0.0) (10 1569.5464945541 1017.2326828983 0.0) (10 1595.6445071905
1010.3280384393 0.0) (10 1613.8763574661 1021.8693438914 0.0))
((0 . "LWPOLYLINE") (100 . "AcDbEntity") (8 . "PLANTS") (62 . 94) (370 . 13) (100 . "AcDbPolyline") (90 . 2) (70 . 0)
(43 . 0.0) (10 1568.6274886878 1217.9496606335) (10 1564.8566742081 1244.3438914027))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1568.6274886878 1217.9496606335 0.0) (10 1582.2185311359 1217.0385007577 0.0) (10 1603.6406155761
1224.6127676594 0.0) (10 1604.8808682867 1241.0578101186 0.0))
((0 . "LWPOLYLINE") (100 . "AcDbEntity") (8 . "PLANTS") (62 . 94) (370 . 13) (100 . "AcDbPolyline") (90 . 2) (70 . 0)
(43 . 0.0) (10 1571.2528605445 1252.2671460327) (10 1564.8566742081 1244.3438914027))
((0 . "LWPOLYLINE") (100 . "AcDbEntity") (8 . "PLANTS") (62 . 94) (370 . 13) (100 . "AcDbPolyline") (90 . 2) (70 . 0)
(43 . 0.0) (10 1572.3981900452 3966.817081448) (10 1572.3981900452 3944.1926470588))
((0 . "LWPOLYLINE") (100 . "AcDbEntity") (8 . "PLANTS") (62 . 94) (370 . 13) (100 . "AcDbPolyline") (90 . 2) (70 . 0)
(43 . 0.0) (10 1572.3981900452 3966.817081448) (10 1610.1055429864 3989.4415158371))
((0 . "LWPOLYLINE") (100 . "AcDbEntity") (8 . "PLANTS") (62 . 94) (370 . 13) (100 . "AcDbPolyline") (90 . 2) (70 . 0)
(43 . 0.0) (10 1572.3981900452 3944.1926470588) (10 1587.4811085973 3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1613.8763574661 3883.8616515837 0.0) (10 1628.2346979572 3913.9503689824 0.0) (10 1591.6396960675
3920.306508044 0.0) (10 1587.4811085973 3944.1926470588 0.0))
((0 . "LWPOLYLINE") (100 . "AcDbEntity") (8 . "PLANTS") (62 . 94) (370 . 13) (100 . "AcDbPolyline") (90 . 2) (70 . 0)
(43 . 0.0) (10 1587.4811085973 3944.1926470588) (10 1598.7933257919 3951.7349547511))
((0 . "LWPOLYLINE") (100 . "AcDbEntity") (8 . "PLANTS") (62 . 94) (370 . 13) (100 . "AcDbPolyline") (90 . 2) (70 . 0)
(43 . 0.0) (10 1621.417760181 1101.0548642534) (10 1591.2519230769 1074.6606334842))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1595.0226244344 3804.6761312217 0.0) (10 1619.5621515486 3804.8543800031 0.0) (10 1602.8010442058
3841.8589117046 0.0) (10 1595.0226244344 3849.925 0.0))
((0 . "LWPOLYLINE") (100 . "AcDbEntity") (8 . "PLANTS") (62 . 94) (370 . 13) (100 . "AcDbPolyline") (90 . 2) (70 . 0)
(43 . 0.0) (10 1598.7933257919 3868.778280543) (10 1595.0226244344 3849.925))
((0 . "LWPOLYLINE") (100 . "AcDbEntity") (8 . "PLANTS") (62 . 94) (370 . 13) (100 . "AcDbPolyline") (90 . 2) (70 . 0)
(43 . 0.0) (10 1598.7933257919 3868.778280543) (10 1606.334841629 3868.778280543))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1681.7496606335 3880.0904977376 0.0) (10 1687.5110167425 3831.5202382581 0.0) (10 1626.299736602
3843.8808564698 0.0) (10 1606.334841629 3868.778280543 0.0))
((0 . "LWPOLYLINE") (100 . "AcDbEntity") (8 . "PLANTS") (62 . 94) (370 . 13) (100 . "AcDbPolyline") (90 . 2) (70 . 0)
(43 . 0.0) (10 1613.8763574661 3883.8616515837) (10 1606.334841629 3868.778280543))
((0 . "LWPOLYLINE") (100 . "AcDbEntity") (8 . "PLANTS") (62 . 94) (370 . 13) (100 . "AcDbPolyline") (90 . 2) (70 . 0)
(43 . 0.0) (10 1621.417760181 1150.0763574661) (10 1606.334841629 1172.7007918552))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.4023000138)
(40 . 0.6092049971) (40 . 0.875859299) (40 . 1) (40 . 1) (40 . 1) (40 . 1) (10 1704.3740950226 1146.3037330317 0.0) (10
1703.615088389 1161.0710153284 0.0) (10 1692.3790443644 1211.865788169 0.0) (10 1649.3023727579 1207.5436976578 0.0) (10
1621.638504909 1184.8753498889 0.0) (10 1602.2551465684 1191.407620389 0.0) (10 1606.3348416289 1172.7007918552 0.0))
((0 . "LWPOLYLINE") (100 . "AcDbEntity") (8 . "PLANTS") (62 . 94) (370 . 13) (100 . "AcDbPolyline") (90 . 2) (70 . 0)
(43 . 0.0) (10 1610.1055429864 4019.6082579186) (10 1610.1055429864 3989.4415158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1610.1055429864 4019.6082579186 0.0) (10 1629.0693838307 4064.0556826516 0.0) (10 1675.4378791945
4006.5212028026 0.0) (10 1644.0421945701 4000.7537330317 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1610.1055429864 3989.4415158371 0.0) (10 1643.7035687749 3989.4478322498 0.0) (10 1634.6634406884
3936.7587524786 0.0) (10 1670.4374434389 3936.6515837104 0.0))
((0 . "LWPOLYLINE") (100 . "AcDbEntity") (8 . "PLANTS") (62 . 94) (370 . 13) (100 . "AcDbPolyline") (90 . 2) (70 . 0)
(43 . 0.0) (10 1613.8763574661 1021.8693438914) (10 1610.1055429864 1048.2664027149))
((0 . "LWPOLYLINE") (100 . "AcDbEntity") (8 . "PLANTS") (62 . 94) (370 . 13) (100 . "AcDbPolyline") (90 . 3) (70 . 0)
(43 . 0.0) (10 1613.8763574661 3883.8616515837) (10 1651.5837104072 3884.0095022624) (10 1670.4374434389
3891.4027149321))
((0 . "LWPOLYLINE") (100 . "AcDbEntity") (8 . "PLANTS") (62 . 94) (370 . 13) (100 . "AcDbPolyline") (90 . 3) (70 . 0)
(43 . 0.0) (10 1613.8763574661 1021.8693438914) (10 1644.0421945701 1018.2472850679) (10 1666.6666289593
1029.4117647059))
((0 . "LWPOLYLINE") (100 . "AcDbEntity") (8 . "PLANTS") (62 . 94) (370 . 13) (100 . "AcDbPolyline") (90 . 2) (70 . 0)
(43 . 0.0) (10 1621.417760181 1101.0548642534) (10 1617.6470588235 1119.9095022624))
((0 . "LWPOLYLINE") (100 . "AcDbEntity") (8 . "PLANTS") (62 . 94) (370 . 13) (100 . "AcDbPolyline") (90 . 3) (70 . 0)
(43 . 0.0) (10 1617.6470588235 1119.9095022624) (10 1621.2696832579 1127.4567873303) (10 1621.417760181
1150.0763574661))
((0 . "LWPOLYLINE") (100 . "AcDbEntity") (8 . "PLANTS") (62 . 94) (370 . 13) (100 . "AcDbPolyline") (90 . 2) (70 . 0)
(43 . 0.0) (10 1821.2669683258 1248.1136877828) (10 1821.0491193433 1303.5696449374))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1674.2081447964 1116.1397058823 0.0) (10 1671.3307729549 1142.8534204648 0.0) (10 1644.1854669064
1155.8554237457 0.0) (10 1621.417760181 1150.0763574661 0.0))
((0 . "LWPOLYLINE") (100 . "AcDbEntity") (8 . "PLANTS") (62 . 94) (370 . 13) (100 . "AcDbPolyline") (90 . 2) (70 . 0)
(43 . 0.0) (10 1621.417760181 1101.0548642534) (10 1647.8130090498 1097.2850678733))
((0 . "LWPOLYLINE") (100 . "AcDbEntity") (8 . "PLANTS") (62 . 94) (370 . 13) (100 . "AcDbPolyline") (90 . 2) (70 . 0)
(43 . 0.0) (10 1666.6666289593 1029.4117647059) (10 1647.8130090498 1097.2850678733))
((0 . "LWPOLYLINE") (100 . "AcDbEntity") (8 . "PLANTS") (62 . 94) (370 . 13) (100 . "AcDbPolyline") (90 . 2) (70 . 0)
(43 . 0.0) (10 1674.2081447964 1116.1397058824) (10 1647.8130090498 1097.2850678733))
((0 . "LWPOLYLINE") (100 . "AcDbEntity") (8 . "PLANTS") (62 . 94) (370 . 13) (100 . "AcDbPolyline") (90 . 2) (70 . 0)
(43 . 0.0) (10 1708.1447963801 1029.4117647059) (10 1666.6666289593 1029.4117647059))
((0 . "LWPOLYLINE") (100 . "AcDbEntity") (8 . "PLANTS") (62 . 94) (370 . 13) (100 . "AcDbPolyline") (90 . 2) (70 . 0)
(43 . 0.0) (10 1677.9788461538 3936.6515837104) (10 1670.4374434389 3936.6515837104))
((0 . "LWPOLYLINE") (100 . "AcDbEntity") (8 . "PLANTS") (62 . 94) (370 . 13) (100 . "AcDbPolyline") (90 . 2) (70 . 0)
(43 . 0.0) (10 1670.4374434389 3936.6515837104) (10 1670.4374434389 3891.4027149321))
((0 . "LWPOLYLINE") (100 . "AcDbEntity") (8 . "PLANTS") (62 . 94) (370 . 13) (100 . "AcDbPolyline") (90 . 2) (70 . 0)
(43 . 0.0) (10 1681.7496606335 3880.0904977376) (10 1670.4374434389 3891.4027149321))
((0 . "LWPOLYLINE") (100 . "AcDbEntity") (8 . "PLANTS") (62 . 94) (370 . 13) (100 . "AcDbPolyline") (90 . 2) (70 . 0)
(43 . 0.0) (10 1674.2081447964 1116.1397058824) (10 1685.520361991 1116.1397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1677.9788461538 3936.6515837104 0.0) (10 1673.3841779746 3967.9688126594 0.0) (10 1704.4701056626
4026.1161967795 0.0) (10 1742.0814479638 4008.2960407241 0.0))
((0 . "LWPOLYLINE") (100 . "AcDbEntity") (8 . "PLANTS") (62 . 94) (370 . 13) (100 . "AcDbPolyline") (90 . 2) (70 . 0)
(43 . 0.0) (10 1677.9788461538 3936.6515837104) (10 1734.5399321267 3940.4227375566))
((0 . "LWPOLYLINE") (100 . "AcDbEntity") (8 . "PLANTS") (62 . 94) (370 . 13) (100 . "AcDbPolyline") (90 . 2) (70 . 0)
(43 . 0.0) (10 1681.7496606335 3880.0904977376) (10 1749.6229638009 3883.8616515837))
((0 . "LWPOLYLINE") (100 . "AcDbEntity") (8 . "PLANTS") (62 . 94) (370 . 13) (100 . "AcDbPolyline") (90 . 2) (70 . 0)
(43 . 0.0) (10 1704.3740950226 1093.5152714932) (10 1685.520361991 1116.1397058824))
((0 . "LWPOLYLINE") (100 . "AcDbEntity") (8 . "PLANTS") (62 . 94) (370 . 13) (100 . "AcDbPolyline") (90 . 3) (70 . 0)
(43 . 0.0) (10 1704.3740950226 1146.3037330317) (10 1703.1697963801 1134.9915158371) (10 1685.520361991
1116.1397058824))
((0 . "LWPOLYLINE") (100 . "AcDbEntity") (8 . "PLANTS") (62 . 94) (370 . 13) (100 . "AcDbPolyline") (90 . 3) (70 . 0)
(43 . 0.0) (10 1749.6229638009 1153.8461538462) (10 1726.9985294118 1146.4521493213) (10 1704.3740950226
1146.3037330317))
((0 . "LWPOLYLINE") (100 . "AcDbEntity") (8 . "PLANTS") (62 . 94) (370 . 13) (100 . "AcDbPolyline") (90 . 2) (70 . 0)
(43 . 0.0) (10 1704.3740950226 1093.5152714932) (10 1704.3740950226 1078.4304298643))
((0 . "LWPOLYLINE") (100 . "AcDbEntity") (8 . "PLANTS") (62 . 94) (370 . 13) (100 . "AcDbPolyline") (90 . 2) (70 . 0)
(43 . 0.0) (10 1743.9668552036 1095.3987556561) (10 1704.3740950226 1093.5152714932))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1708.1447963801 1029.4117647059 0.0) (10 1726.0287476443 1011.9609115074 0.0) (10 1754.3602754065
1020.376202407 0.0) (10 1776.0180995475 1025.6419683258 0.0))
((0 . "LWPOLYLINE") (100 . "AcDbEntity") (8 . "PLANTS") (62 . 94) (370 . 13) (100 . "AcDbPolyline") (90 . 3) (70 . 0)
(43 . 0.0) (10 1742.0814479638 1070.8908371041) (10 1719.6050904977 1055.6589366516) (10 1708.1447963801
1029.4117647059))
((0 . "LWPOLYLINE") (100 . "AcDbEntity") (8 . "PLANTS") (62 . 94) (370 . 13) (100 . "AcDbPolyline") (90 . 2) (70 . 0)
(43 . 0.0) (10 1753.3936651584 3921.5682126697) (10 1734.5399321267 3940.4227375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1734.5399321267 3940.4227375566 0.0) (10 1729.674479936 3956.4680210503 0.0) (10 1752.2601695859
3966.791080498 0.0) (10 1764.7058823529 3959.2760180995 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1742.0814479638 1070.8908371041 0.0) (10 1758.3722231176 1061.5794934975 0.0) (10 1774.8941050842
1045.2480546945 0.0) (10 1776.0180995475 1025.6419683258 0.0))
((0 . "LWPOLYLINE") (100 . "AcDbEntity") (8 . "PLANTS") (62 . 94) (370 . 13) (100 . "AcDbPolyline") (90 . 2) (70 . 0)
(43 . 0.0) (10 1743.9668552036 1095.3987556561) (10 1742.0814479638 1070.8908371041))
((0 . "LWPOLYLINE") (100 . "AcDbEntity") (8 . "PLANTS") (62 . 94) (370 . 13) (100 . "AcDbPolyline") (90 . 2) (70 . 0)
(43 . 0.0) (10 1743.9668552036 1095.3987556561) (10 1794.8718325792 1093.5152714932))
((0 . "LWPOLYLINE") (100 . "AcDbEntity") (8 . "PLANTS") (62 . 94) (370 . 13) (100 . "AcDbPolyline") (90 . 2) (70 . 0)
(43 . 0.0) (10 1743.9668552036 1095.3987556561) (10 1753.3936651584 1116.1397058824))
((0 . "LWPOLYLINE") (100 . "AcDbEntity") (8 . "PLANTS") (62 . 94) (370 . 13) (100 . "AcDbPolyline") (90 . 2) (70 . 0)
(43 . 0.0) (10 1753.3936651584 3921.5682126697) (10 1749.6229638009 3883.8616515837))
((0 . "LWPOLYLINE") (100 . "AcDbEntity") (8 . "PLANTS") (62 . 94) (370 . 13) (100 . "AcDbPolyline") (90 . 3) (70 . 0)
(43 . 0.0) (10 1794.8718325792 3887.631561086) (10 1783.5595022624 3884.0095022624) (10 1749.6229638009
3883.8616515837))
((0 . "LWPOLYLINE") (100 . "AcDbEntity") (8 . "PLANTS") (62 . 94) (370 . 13) (100 . "AcDbPolyline") (90 . 2) (70 . 0)
(43 . 0.0) (10 1749.6229638009 1153.8461538462) (10 1749.6229638009 1184.0130090498))
((0 . "LWPOLYLINE") (100 . "AcDbEntity") (8 . "PLANTS") (62 . 94) (370 . 13) (100 . "AcDbPolyline") (90 . 2) (70 . 0)
(43 . 0.0) (10 1776.0180995475 1248.1136877828) (10 1770.2661870806 1265.4824457403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1732.0511711702 1236.8211838075 0.0) (10 1736.3108431598 1222.3463856728 0.0) (10 1729.8181624189
1191.1236437816 0.0) (10 1749.6229638009 1184.0130090498 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1783.5596153846 1168.9281674208 0.0) (10 1783.7329313878 1188.0423687232 0.0) (10 1761.3738506956
1193.0786789673 0.0) (10 1749.6229638009 1184.0130090498 0.0))
((0 . "LWPOLYLINE") (100 . "AcDbEntity") (8 . "PLANTS") (62 . 94) (370 . 13) (100 . "AcDbPolyline") (90 . 2) (70 . 0)
(43 . 0.0) (10 1779.788800905 1153.8461538462) (10 1749.6229638009 1153.8461538462))
((0 . "LWPOLYLINE") (100 . "AcDbEntity") (8 . "PLANTS") (62 . 94) (370 . 13) (100 . "AcDbPolyline") (90 . 2) (70 . 0)
(43 . 0.0) (10 1794.8718325792 3917.7983031674) (10 1753.3936651584 3921.5682126697))
((0 . "LWPOLYLINE") (100 . "AcDbEntity") (8 . "PLANTS") (62 . 94) (370 . 13) (100 . "AcDbPolyline") (90 . 2) (70 . 0)
(43 . 0.0) (10 1768.4765837104 4083.7104072398) (10 1768.4765837104 4076.1693438914))
((0 . "LWPOLYLINE") (100 . "AcDbEntity") (8 . "PLANTS") (62 . 94) (370 . 13) (100 . "AcDbPolyline") (90 . 3) (70 . 0)
(43 . 0.0) (10 1817.4962669683 4074.2831447964) (10 1783.5596153846 4072.5462669683) (10 1768.4765837104
4076.1693438914))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.2158095342)
(40 . 0.5457949655) (40 . 0.8309714737) (40 . 1) (40 . 1) (40 . 1) (40 . 1) (10 1813.7254524887 3981.9004524887 0.0) (10
1804.3705782477 3975.3535130596 0.0) (10 1770.2231464362 3984.4160560236 0.0) (10 1792.3652033855 4036.1347914126 0.0)
(10 1741.98069081 4046.918295092 0.0) (10 1759.4341795036 4071.8821311382 0.0) (10 1768.4765837104 4076.1693438914 0.0))
((0 . "LWPOLYLINE") (100 . "AcDbEntity") (8 . "PLANTS") (62 . 94) (370 . 13) (100 . "AcDbPolyline") (90 . 3) (70 . 0)
(43 . 0.0) (10 1776.0180995475 1248.1136877828) (10 1769.6808823529 1236.8090497738) (10 1772.24739819 1229.2618778281))
((0 . "LWPOLYLINE") (100 . "AcDbEntity") (8 . "PLANTS") (62 . 94) (370 . 13) (100 . "AcDbPolyline") (90 . 3) (70 . 0)
(43 . 0.0) (10 1776.0180995475 3842.3826923077) (10 1798.6425339367 3846.0057692308) (10 1825.0376696833
3838.6127828054))
((0 . "LWPOLYLINE") (100 . "AcDbEntity") (8 . "PLANTS") (62 . 94) (370 . 13) (100 . "AcDbPolyline") (90 . 2) (70 . 0)
(43 . 0.0) (10 1821.2669683258 1248.1136877828) (10 1776.0180995475 1248.1136877828))
((0 . "LWPOLYLINE") (100 . "AcDbEntity") (8 . "PLANTS") (62 . 94) (370 . 13) (100 . "AcDbPolyline") (90 . 2) (70 . 0)
(43 . 0.0) (10 1821.2669683258 1025.6419683258) (10 1776.0180995475 1025.6419683258))
((0 . "LWPOLYLINE") (100 . "AcDbEntity") (8 . "PLANTS") (62 . 94) (370 . 13) (100 . "AcDbPolyline") (90 . 3) (70 . 0)
(43 . 0.0) (10 1779.788800905 1153.8461538462) (10 1784.6158371041 1112.367081448) (10 1794.8718325792 1093.5152714932))
((0 . "LWPOLYLINE") (100 . "AcDbEntity") (8 . "PLANTS") (62 . 94) (370 . 13) (100 . "AcDbPolyline") (90 . 2) (70 . 0)
(43 . 0.0) (10 1783.5596153846 1168.9281674208) (10 1779.788800905 1153.8461538462))
((0 . "LWPOLYLINE") (100 . "AcDbEntity") (8 . "PLANTS") (62 . 94) (370 . 13) (100 . "AcDbPolyline") (90 . 2) (70 . 0)
(43 . 0.0) (10 1783.5596153846 1168.9281674208) (10 1821.2669683258 1168.9281674208))
((0 . "LWPOLYLINE") (100 . "AcDbEntity") (8 . "PLANTS") (62 . 94) (370 . 13) (100 . "AcDbPolyline") (90 . 2) (70 . 0)
(43 . 0.0) (10 1794.8718325792 3917.7983031674) (10 1794.8718325792 3887.631561086))
((0 . "LWPOLYLINE") (100 . "AcDbEntity") (8 . "PLANTS") (62 . 94) (370 . 13) (100 . "AcDbPolyline") (90 . 2) (70 . 0)
(43 . 0.0) (10 1794.8718325792 3917.7983031674) (10 1834.4645927602 3934.7666289593))
((0 . "LWPOLYLINE") (100 . "AcDbEntity") (8 . "PLANTS") (62 . 94) (370 . 13) (100 . "AcDbPolyline") (90 . 2) (70 . 0)
(43 . 0.0) (10 1794.8718325792 3887.631561086) (10 1836.3498868778 3887.631561086))
((0 . "LWPOLYLINE") (100 . "AcDbEntity") (8 . "PLANTS") (62 . 94) (370 . 13) (100 . "AcDbPolyline") (90 . 2) (70 . 0)
(43 . 0.0) (10 1821.2669683258 1093.5152714932) (10 1794.8718325792 1093.5152714932))
((0 . "LWPOLYLINE") (100 . "AcDbEntity") (8 . "PLANTS") (62 . 94) (370 . 13) (100 . "AcDbPolyline") (90 . 3) (70 . 0)
(43 . 0.0) (10 1834.4645927602 3934.7666289593) (10 1822.3233031674 3951.7349547511) (10 1813.7254524887
3981.9004524887))
((0 . "LWPOLYLINE") (100 . "AcDbEntity") (8 . "PLANTS") (62 . 94) (370 . 13) (100 . "AcDbPolyline") (90 . 3) (70 . 0)
(43 . 0.0) (10 1817.4962669683 4074.2831447964) (10 1817.3481900452 3989.4484162896) (10 1813.7254524887
3981.9004524887))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1817.4962669683 4074.2831447964 0.0) (10 1838.8462427271 4066.522660811 0.0) (10 1861.2231542113
4085.9182583477 0.0) (10 1858.974321267 4106.334841629 0.0))
((0 . "LWPOLYLINE") (100 . "AcDbEntity") (8 . "PLANTS") (62 . 94) (370 . 13) (100 . "AcDbPolyline") (90 . 2) (70 . 0)
(43 . 0.0) (10 1821.2669683258 1248.1136877828) (10 1821.2669683258 1168.9281674208))
((0 . "LWPOLYLINE") (100 . "AcDbEntity") (8 . "PLANTS") (62 . 94) (370 . 13) (100 . "AcDbPolyline") (90 . 3) (70 . 0)
(43 . 0.0) (10 1821.2669683258 1093.5152714932) (10 1821.2669683258 1157.6159502262) (10 1821.2669683258
1168.9281674208))
((0 . "LWPOLYLINE") (100 . "AcDbEntity") (8 . "PLANTS") (62 . 94) (370 . 13) (100 . "AcDbPolyline") (90 . 2) (70 . 0)
(43 . 0.0) (10 1821.2669683258 1093.5152714932) (10 1828.8084841629 1093.5152714932))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1881.5987556561 1029.4117647059 0.0) (10 1867.3949146749 1016.4080703298 0.0) (10 1834.1896610249
1005.4512010369 0.0) (10 1821.2669683258 1025.6419683258 0.0))
((0 . "LWPOLYLINE") (100 . "AcDbEntity") (8 . "PLANTS") (62 . 94) (370 . 13) (100 . "AcDbPolyline") (90 . 2) (70 . 0)
(43 . 0.0) (10 1828.8084841629 1093.5152714932) (10 1821.2669683258 1025.6419683258))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1825.0376696833 3838.6127828054 0.0) (10 1808.4771239034 3826.7072467998 0.0) (10 1828.6063626008
3792.9743717026 0.0) (10 1843.8914027149 3808.446040724 0.0))
((0 . "LWPOLYLINE") (100 . "AcDbEntity") (8 . "PLANTS") (62 . 94) (370 . 13) (100 . "AcDbPolyline") (90 . 2) (70 . 0)
(43 . 0.0) (10 1825.0376696833 3838.6127828054) (10 1843.8914027149 3846.1538461538))
((0 . "LWPOLYLINE") (100 . "AcDbEntity") (8 . "PLANTS") (62 . 94) (370 . 13) (100 . "AcDbPolyline") (90 . 3) (70 . 0)
(43 . 0.0) (10 1877.8280542986 1101.0548642534) (10 1862.7451357466 1093.6630090498) (10 1828.8084841629
1093.5152714932))
((0 . "LWPOLYLINE") (100 . "AcDbEntity") (8 . "PLANTS") (62 . 94) (370 . 13) (100 . "AcDbPolyline") (90 . 2) (70 . 0)
(43 . 0.0) (10 1834.4645927602 3934.7666289593) (10 1836.3498868778 3887.631561086))
((0 . "LWPOLYLINE") (100 . "AcDbEntity") (8 . "PLANTS") (62 . 94) (370 . 13) (100 . "AcDbPolyline") (90 . 3) (70 . 0)
(43 . 0.0) (10 1834.4645927602 3934.7666289593) (10 1847.6589366516 3940.2709276018) (10 1913.6503393665
3944.1926470588))
((0 . "LWPOLYLINE") (100 . "AcDbEntity") (8 . "PLANTS") (62 . 94) (370 . 13) (100 . "AcDbPolyline") (90 . 2) (70 . 0)
(43 . 0.0) (10 1843.8914027149 3883.8616515837) (10 1836.3498868778 3887.631561086))
((0 . "LWPOLYLINE") (100 . "AcDbEntity") (8 . "PLANTS") (62 . 94) (370 . 13) (100 . "AcDbPolyline") (90 . 3) (70 . 0)
(43 . 0.0) (10 1900.4524886878 3985.6716063348) (10 1862.7516968326 3990.6462669683) (10 1843.8914027149
4023.3781674208))
((0 . "LWPOLYLINE") (100 . "AcDbEntity") (8 . "PLANTS") (62 . 94) (370 . 13) (100 . "AcDbPolyline") (90 . 3) (70 . 0)
(43 . 0.0) (10 1843.8914027149 3883.8616515837) (10 1874.0573529412 3882.8049773756) (10 1891.0259049774
3870.6632352941))
((0 . "LWPOLYLINE") (100 . "AcDbEntity") (8 . "PLANTS") (62 . 94) (370 . 13) (100 . "AcDbPolyline") (90 . 2) (70 . 0)
(43 . 0.0) (10 1843.8914027149 3883.8616515837) (10 1843.8914027149 3846.1538461538))
((0 . "LWPOLYLINE") (100 . "AcDbEntity") (8 . "PLANTS") (62 . 94) (370 . 13) (100 . "AcDbPolyline") (90 . 3) (70 . 0)
(43 . 0.0) (10 1891.0259049774 3870.6632352941) (10 1866.5158371041 3847.3583710407) (10 1843.8914027149
3846.1538461538))
((0 . "LWPOLYLINE") (100 . "AcDbEntity") (8 . "PLANTS") (62 . 94) (370 . 13) (100 . "AcDbPolyline") (90 . 2) (70 . 0)
(43 . 0.0) (10 1847.6621040724 1165.1583710407) (10 1851.432918552 1172.7007918552))
((0 . "LWPOLYLINE") (100 . "AcDbEntity") (8 . "PLANTS") (62 . 94) (370 . 13) (100 . "AcDbPolyline") (90 . 2) (70 . 0)
(43 . 0.0) (10 1851.432918552 1259.4259049774) (10 1855.2036199095 1244.3438914027))
((0 . "LWPOLYLINE") (100 . "AcDbEntity") (8 . "PLANTS") (62 . 94) (370 . 13) (100 . "AcDbPolyline") (90 . 2) (70 . 0)
(43 . 0.0) (10 1885.3695701357 1168.9281674208) (10 1851.432918552 1172.7007918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1855.2036199095 1244.3438914027 0.0) (10 1840.8111274639 1223.7604675743 0.0) (10 1842.751975135
1195.3630972651 0.0) (10 1851.432918552 1172.7007918552 0.0))
((0 . "LWPOLYLINE") (100 . "AcDbEntity") (8 . "PLANTS") (62 . 94) (370 . 13) (100 . "AcDbPolyline") (90 . 2) (70 . 0)
(43 . 0.0) (10 1855.2036199095 4053.5449095023) (10 1855.2036199095 4061.0859728507))
((0 . "LWPOLYLINE") (100 . "AcDbEntity") (8 . "PLANTS") (62 . 94) (370 . 13) (100 . "AcDbPolyline") (90 . 2) (70 . 0)
(43 . 0.0) (10 1892.9109728507 1244.3438914027) (10 1855.2036199095 1244.3438914027))
((0 . "LWPOLYLINE") (100 . "AcDbEntity") (8 . "PLANTS") (62 . 94) (370 . 13) (100 . "AcDbPolyline") (90 . 2) (70 . 0)
(43 . 0.0) (10 1889.1402714932 1101.0548642534) (10 1877.8280542986 1101.0548642534))
((0 . "LWPOLYLINE") (100 . "AcDbEntity") (8 . "PLANTS") (62 . 94) (370 . 13) (100 . "AcDbPolyline") (90 . 3) (70 . 0)
(43 . 0.0) (10 1877.8280542986 1101.0548642534) (10 1885.2214932127 1138.7641402715) (10 1885.3695701357
1168.9281674208))
((0 . "LWPOLYLINE") (100 . "AcDbEntity") (8 . "PLANTS") (62 . 94) (370 . 13) (100 . "AcDbPolyline") (90 . 2) (70 . 0)
(43 . 0.0) (10 1911.7647058824 1025.6419683258) (10 1881.5987556561 1029.4117647059))
((0 . "LWPOLYLINE") (100 . "AcDbEntity") (8 . "PLANTS") (62 . 94) (370 . 13) (100 . "AcDbPolyline") (90 . 2) (70 . 0)
(43 . 0.0) (10 1889.1402714932 1101.0548642534) (10 1881.5987556561 1029.4117647059))
((0 . "LWPOLYLINE") (100 . "AcDbEntity") (8 . "PLANTS") (62 . 94) (370 . 13) (100 . "AcDbPolyline") (90 . 2) (70 . 0)
(43 . 0.0) (10 1892.9109728507 1180.2403846154) (10 1885.3695701357 1168.9281674208))
((0 . "LWPOLYLINE") (100 . "AcDbEntity") (8 . "PLANTS") (62 . 94) (370 . 13) (100 . "AcDbPolyline") (90 . 2) (70 . 0)
(43 . 0.0) (10 1889.1402714932 1101.0548642534) (10 1907.9942307692 1101.0548642534))
((0 . "LWPOLYLINE") (100 . "AcDbEntity") (8 . "PLANTS") (62 . 94) (370 . 13) (100 . "AcDbPolyline") (90 . 3) (70 . 0)
(43 . 0.0) (10 1891.0259049774 3870.6632352941) (10 1900.3849547511 3865.2294117647) (10 1938.1596153846
3865.0071266968))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4379543878) (40
. 1) (40 . 1) (40 . 1) (40 . 1) (10 1891.0259049774 3870.6632352941 0.0) (10 1897.7071670788 3879.9569540178 0.0) (10
1901.101641096 3905.7780594624 0.0) (10 1912.8825471593 3930.2482998824 0.0) (10 1913.6503393666 3944.1926470588 0.0))
((0 . "LWPOLYLINE") (100 . "AcDbEntity") (8 . "PLANTS") (62 . 94) (370 . 13) (100 . "AcDbPolyline") (90 . 2) (70 . 0)
(43 . 0.0) (10 1892.9109728507 1244.3438914027) (10 1892.9109728507 1251.8863122172))
((0 . "LWPOLYLINE") (100 . "AcDbEntity") (8 . "PLANTS") (62 . 94) (370 . 13) (100 . "AcDbPolyline") (90 . 2) (70 . 0)
(43 . 0.0) (10 2209.6528280543 1308.44739819) (10 2209.1043391531 1393.4689538609))
((0 . "LWPOLYLINE") (100 . "AcDbEntity") (8 . "PLANTS") (62 . 94) (370 . 13) (100 . "AcDbPolyline") (90 . 2) (70 . 0)
(43 . 0.0) (10 1892.9109728507 1335.7843396493) (10 1892.9109728507 1251.8863122172))
((0 . "LWPOLYLINE") (100 . "AcDbEntity") (8 . "PLANTS") (62 . 94) (370 . 13) (100 . "AcDbPolyline") (90 . 2) (70 . 0)
(43 . 0.0) (10 1926.84739819 1255.6561085973) (10 1892.9109728507 1251.8863122172))
((0 . "LWPOLYLINE") (100 . "AcDbEntity") (8 . "PLANTS") (62 . 94) (370 . 13) (100 . "AcDbPolyline") (90 . 2) (70 . 0)
(43 . 0.0) (10 1892.9109728507 1244.3438914027) (10 1892.9109728507 1180.2403846154))
((0 . "LWPOLYLINE") (100 . "AcDbEntity") (8 . "PLANTS") (62 . 94) (370 . 13) (100 . "AcDbPolyline") (90 . 3) (70 . 0)
(43 . 0.0) (10 1892.9109728507 1180.2403846154) (10 1900.4524886878 1180.2403846154) (10 1904.2229638009
1184.0130090498))
((0 . "LWPOLYLINE") (100 . "AcDbEntity") (8 . "PLANTS") (62 . 94) (370 . 13) (100 . "AcDbPolyline") (90 . 2) (70 . 0)
(43 . 0.0) (10 1900.4524886878 3985.6716063348) (10 1900.4524886878 3996.9838235294))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1900.4524886878 3996.9838235294 0.0) (10 1860.9648881615 4044.8895596439 0.0) (10 1935.9933359199
4115.0196766304 0.0) (10 1893.0272089647 4163.7587259634 0.0))
((0 . "LWPOLYLINE") (100 . "AcDbEntity") (8 . "PLANTS") (62 . 94) (370 . 13) (100 . "AcDbPolyline") (90 . 3) (70 . 0)
(43 . 0.0) (10 2209.4927161976 4221.9671119828) (10 2209.6462669683 4166.667081448) (10 2205.8823529412
4125.1881221719))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1972.0962669683 4023.3781674208 0.0) (10 1949.7539619227 4042.3374025458 0.0) (10 1908.9442460104
4027.1019744257 0.0) (10 1900.4524886878 3996.9838235294 0.0))
((0 . "LWPOLYLINE") (100 . "AcDbEntity") (8 . "PLANTS") (62 . 94) (370 . 13) (100 . "AcDbPolyline") (90 . 3) (70 . 0)
(43 . 0.0) (10 1900.4524886878 3985.6716063348) (10 1901.5084841629 3970.5882352941) (10 1913.6503393665
3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1907.9942307692 1101.0548642534 0.0) (10 1929.914245948 1082.9363978887 0.0) (10 1937.8360981841
1044.4042676785 0.0) (10 1911.7647058823 1025.6419683258 0.0))
((0 . "LWPOLYLINE") (100 . "AcDbEntity") (8 . "PLANTS") (62 . 94) (370 . 13) (100 . "AcDbPolyline") (90 . 2) (70 . 0)
(43 . 0.0) (10 1907.9942307692 1101.0548642534) (10 1926.84739819 1108.5972850679))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1911.7647058824 1025.6419683258 0.0) (10 1934.8874658125 1011.8778984943 0.0) (10 1968.1306610728
1019.5577536534 0.0) (10 1987.1797511312 1036.9541855204 0.0))
((0 . "LWPOLYLINE") (100 . "AcDbEntity") (8 . "PLANTS") (62 . 94) (370 . 13) (100 . "AcDbPolyline") (90 . 2) (70 . 0)
(43 . 0.0) (10 1923.0769230769 3944.1926470588) (10 1913.6503393665 3944.1926470588))
((0 . "LWPOLYLINE") (100 . "AcDbEntity") (8 . "PLANTS") (62 . 94) (370 . 13) (100 . "AcDbPolyline") (90 . 3) (70 . 0)
(43 . 0.0) (10 1923.0769230769 3944.1926470588) (10 1941.9308823529 3929.264479638) (10 1998.4919683258 3929.110520362))
((0 . "LWPOLYLINE") (100 . "AcDbEntity") (8 . "PLANTS") (62 . 94) (370 . 13) (100 . "AcDbPolyline") (90 . 3) (70 . 0)
(43 . 0.0) (10 1923.0769230769 3944.1926470588) (10 1938.1596153846 3958.2193438914) (10 1960.7840497738
3966.817081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1926.84739819 1108.5972850679 0.0) (10 1919.7565447325 1127.3890033243 0.0) (10 1931.6190690513
1154.3003137265 0.0) (10 1953.2430995475 1153.8461538462 0.0))
((0 . "LWPOLYLINE") (100 . "AcDbEntity") (8 . "PLANTS") (62 . 94) (370 . 13) (100 . "AcDbPolyline") (90 . 3) (70 . 0)
(43 . 0.0) (10 1926.84739819 1108.5972850679) (10 1964.5549773756 1117.3368778281) (10 1975.8675339367 1131.221719457))
((0 . "LWPOLYLINE") (100 . "AcDbEntity") (8 . "PLANTS") (62 . 94) (370 . 13) (100 . "AcDbPolyline") (90 . 2) (70 . 0)
(43 . 0.0) (10 1934.3891402715 3763.1971719457) (10 1931.2471468026 3744.3438914027))
((0 . "LWPOLYLINE") (100 . "AcDbEntity") (8 . "PLANTS") (62 . 94) (370 . 13) (100 . "AcDbPolyline") (90 . 2) (70 . 0)
(43 . 0.0) (10 1941.9308823529 1199.0950226244) (10 1930.6186651584 1195.3252262443))
((0 . "LWPOLYLINE") (100 . "AcDbEntity") (8 . "PLANTS") (62 . 94) (370 . 13) (100 . "AcDbPolyline") (90 . 2) (70 . 0)
(43 . 0.0) (10 1934.3891402715 3763.1971719457) (10 1945.7013574661 3766.9683257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2006.032918552 3865.0071266968 0.0) (10 1993.0906215575 3843.1457015433 0.0) (10 1947.793452876
3834.0674491877 0.0) (10 1938.1596153846 3865.0071266968 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2006.032918552 3865.0071266968 0.0) (10 1992.0536388498 3890.5845481263 0.0) (10 1952.5981667919
3889.3566002971 0.0) (10 1938.1596153846 3865.0071266968 0.0))
((0 . "LWPOLYLINE") (100 . "AcDbEntity") (8 . "PLANTS") (62 . 94) (370 . 13) (100 . "AcDbPolyline") (90 . 2) (70 . 0)
(43 . 0.0) (10 1960.7840497738 1187.7828054299) (10 1941.9308823529 1199.0950226244))
((0 . "LWPOLYLINE") (100 . "AcDbEntity") (8 . "PLANTS") (62 . 94) (370 . 13) (100 . "AcDbPolyline") (90 . 3) (70 . 0)
(43 . 0.0) (10 1957.0135746606 1225.4892533937) (10 1946.7573529412 1214.1770361991) (10 1941.9308823529
1199.0950226244))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.4005432774)
(40 . 0.6215257962) (40 . 0.7608951992) (40 . 1) (40 . 1) (40 . 1) (40 . 1) (10 2006.032918552 3865.0071266968 0.0) (10
2013.531900573 3843.6998174471 0.0) (10 2012.0729029532 3811.53637057 0.0) (10 1975.7372424287 3808.6131836557 0.0) (10
1951.722222069 3795.5866489279 0.0) (10 1944.8558529289 3778.1223158904 0.0) (10 1945.7013574661 3766.9683257918 0.0))
((0 . "LWPOLYLINE") (100 . "AcDbEntity") (8 . "PLANTS") (62 . 94) (370 . 13) (100 . "AcDbPolyline") (90 . 2) (70 . 0)
(43 . 0.0) (10 1945.7013574661 3766.9683257919) (10 1994.7207013575 3770.739479638))
((0 . "LWPOLYLINE") (100 . "AcDbEntity") (8 . "PLANTS") (62 . 94) (370 . 13) (100 . "AcDbPolyline") (90 . 2) (70 . 0)
(43 . 0.0) (10 2124.811199095 3301.2817873303) (10 2074.9910231583 3300.7575104915))
((0 . "LWPOLYLINE") (100 . "AcDbEntity") (8 . "PLANTS") (62 . 94) (370 . 13) (100 . "AcDbPolyline") (90 . 2) (70 . 0)
(43 . 0.0) (10 1975.8675339367 1131.221719457) (10 1953.2430995475 1153.8461538462))
((0 . "LWPOLYLINE") (100 . "AcDbEntity") (8 . "PLANTS") (62 . 94) (370 . 13) (100 . "AcDbPolyline") (90 . 2) (70 . 0)
(43 . 0.0) (10 1960.7840497738 1187.7828054299) (10 1953.2430995475 1153.8461538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1960.7840497738 1187.7828054299 0.0) (10 1997.1212510638 1184.3587164026 0.0) (10 2028.7906142353
1240.9604828824 0.0) (10 2062.5940045249 1206.6374434389 0.0))
((0 . "LWPOLYLINE") (100 . "AcDbEntity") (8 . "PLANTS") (62 . 94) (370 . 13) (100 . "AcDbPolyline") (90 . 2) (70 . 0)
(43 . 0.0) (10 2006.032918552 1131.221719457) (10 1975.8675339367 1131.221719457))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7353915851) (40
. 1) (40 . 1) (40 . 1) (40 . 1) (10 2104.0723981901 3981.9004524887 0.0) (10 2090.8672180727 4016.5710150621 0.0) (10
2031.4838680066 4018.1939986059 0.0) (10 1998.064776953 4052.4490447329 0.0) (10 1987.1797511313 4057.3148190047 0.0))
((0 . "LWPOLYLINE") (100 . "AcDbEntity") (8 . "PLANTS") (62 . 94) (370 . 13) (100 . "AcDbPolyline") (90 . 3) (70 . 0)
(43 . 0.0) (10 1987.1797511312 3963.0471719457) (10 2009.8041855204 3973.3027149321) (10 2039.9695701357
3978.1292986425))
((0 . "LWPOLYLINE") (100 . "AcDbEntity") (8 . "PLANTS") (62 . 94) (370 . 13) (100 . "AcDbPolyline") (90 . 2) (70 . 0)
(43 . 0.0) (10 1998.4919683258 1036.9541855204) (10 1987.1797511312 1036.9541855204))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1987.1797511312 1036.9541855204 0.0) (10 1986.7819050149 1068.1397348048 0.0) (10 2014.4710614569
1107.6632002114 0.0) (10 2051.2817873303 1089.7426470588 0.0))
((0 . "LWPOLYLINE") (100 . "AcDbEntity") (8 . "PLANTS") (62 . 94) (370 . 13) (100 . "AcDbPolyline") (90 . 2) (70 . 0)
(43 . 0.0) (10 2006.032918552 3865.0071266968) (10 1998.4919683258 3929.110520362))
((0 . "LWPOLYLINE") (100 . "AcDbEntity") (8 . "PLANTS") (62 . 94) (370 . 13) (100 . "AcDbPolyline") (90 . 3) (70 . 0)
(43 . 0.0) (10 2043.7408371041 3947.963800905) (10 2017.3451357466 3934.078280543) (10 1998.4919683258 3929.110520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2107.8428733032 1025.6419683258 0.0) (10 2074.0071950763 1017.9565012571 0.0) (10 2018.1244776422
997.2514186607 0.0) (10 1998.4919683258 1036.9541855204 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1998.4919683258 1036.9541855204 0.0) (10 2009.272734392 1067.4995836384 0.0) (10 2060.0801597576
1046.5246616166 0.0) (10 2051.2817873303 1089.7426470588 0.0))
((0 . "LWPOLYLINE") (100 . "AcDbEntity") (8 . "PLANTS") (62 . 94) (370 . 13) (100 . "AcDbPolyline") (90 . 2) (70 . 0)
(43 . 0.0) (10 2006.032918552 3865.0071266968) (10 2017.3451357466 3865.0071266968))
((0 . "LWPOLYLINE") (100 . "AcDbEntity") (8 . "PLANTS") (62 . 94) (370 . 13) (100 . "AcDbPolyline") (90 . 3) (70 . 0)
(43 . 0.0) (10 2047.5113122172 1131.221719457) (10 2017.3454751131 1124.8841628959) (10 2006.032918552 1131.221719457))
((0 . "LWPOLYLINE") (100 . "AcDbEntity") (8 . "PLANTS") (62 . 94) (370 . 13) (100 . "AcDbPolyline") (90 . 3) (70 . 0)
(43 . 0.0) (10 2006.032918552 1131.221719457) (10 2021.1164027149 1149.9279411765) (10 2043.7408371041 1161.3885746606))
((0 . "LWPOLYLINE") (100 . "AcDbEntity") (8 . "PLANTS") (62 . 94) (370 . 13) (100 . "AcDbPolyline") (90 . 2) (70 . 0)
(43 . 0.0) (10 2051.2817873303 3672.6994343891) (10 2013.5746606335 3672.6994343891))
((0 . "LWPOLYLINE") (100 . "AcDbEntity") (8 . "PLANTS") (62 . 94) (370 . 13) (100 . "AcDbPolyline") (90 . 3) (70 . 0)
(43 . 0.0) (10 2017.3451357466 3593.5145927602) (10 2016.2891402715 3616.1390271493) (10 2014.2642374823
3619.6292784388))
((0 . "LWPOLYLINE") (100 . "AcDbEntity") (8 . "PLANTS") (62 . 94) (370 . 13) (100 . "AcDbPolyline") (90 . 2) (70 . 0)
(43 . 0.0) (10 2010.0733341836 3666.4495262289) (10 2013.5746606335 3672.6994343891))
((0 . "LWPOLYLINE") (100 . "AcDbEntity") (8 . "PLANTS") (62 . 94) (370 . 13) (100 . "AcDbPolyline") (90 . 2) (70 . 0)
(43 . 0.0) (10 2013.5746606335 3672.6994343891) (10 2021.1164027149 3714.1783936652))
((0 . "LWPOLYLINE") (100 . "AcDbEntity") (8 . "PLANTS") (62 . 94) (370 . 13) (100 . "AcDbPolyline") (90 . 2) (70 . 0)
(43 . 0.0) (10 2073.9062217195 592.0050904977) (10 2042.3614495108 592.0050904977))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2096.5306561086 3853.6949095023 0.0) (10 2068.6212161388 3863.0421915813 0.0) (10 2035.0856407234
3824.9218745918 0.0) (10 2017.3451357466 3865.0071266968 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2126.6968325792 3906.4860859729 0.0) (10 2088.0001032646 3929.0587986107 0.0) (10 2044.3212354809
3891.3591747116 0.0) (10 2017.3451357466 3865.0071266969 0.0))
((0 . "LWPOLYLINE") (100 . "AcDbEntity") (8 . "PLANTS") (62 . 94) (370 . 13) (100 . "AcDbPolyline") (90 . 2) (70 . 0)
(43 . 0.0) (10 2017.3451357466 3593.5145927602) (10 2036.1990950226 3593.5145927602))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2111.6141402715 3770.739479638 0.0) (10 2077.4690226826 3773.03229763 0.0) (10 2000.7852565917
3780.6652115187 0.0) (10 2021.1164027149 3714.1783936652 0.0))
((0 . "LWPOLYLINE") (100 . "AcDbEntity") (8 . "PLANTS") (62 . 94) (370 . 13) (100 . "AcDbPolyline") (90 . 2) (70 . 0)
(43 . 0.0) (10 2039.9695701357 3717.9483031674) (10 2021.1164027149 3714.1783936652))
((0 . "LWPOLYLINE") (100 . "AcDbEntity") (8 . "PLANTS") (62 . 94) (370 . 13) (100 . "AcDbPolyline") (90 . 2) (70 . 0)
(43 . 0.0) (10 2081.4479638009 3631.221719457) (10 2036.1990950226 3627.4505656109))
((0 . "LWPOLYLINE") (100 . "AcDbEntity") (8 . "PLANTS") (62 . 94) (370 . 13) (100 . "AcDbPolyline") (90 . 2) (70 . 0)
(43 . 0.0) (10 2055.0530542986 3438.9140271493) (10 2041.6150015273 3422.7885895798))
((0 . "LWPOLYLINE") (100 . "AcDbEntity") (8 . "PLANTS") (62 . 94) (370 . 13) (100 . "AcDbPolyline") (90 . 2) (70 . 0)
(43 . 0.0) (10 2043.7408371041 3947.963800905) (10 2039.9695701357 3978.1292986425))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2039.9695701357 3978.1292986425 0.0) (10 2054.0730321575 4003.2378872255 0.0) (10 2084.3631676936
3960.3727350925 0.0) (10 2104.07239819 3981.9004524887 0.0))
((0 . "LWPOLYLINE") (100 . "AcDbEntity") (8 . "PLANTS") (62 . 94) (370 . 13) (100 . "AcDbPolyline") (90 . 3) (70 . 0)
(43 . 0.0) (10 2043.7408371041 3947.963800905) (10 2126.6968325792 3948.118438914) (10 2141.7795248869 3959.2760180995))
((0 . "LWPOLYLINE") (100 . "AcDbEntity") (8 . "PLANTS") (62 . 94) (370 . 13) (100 . "AcDbPolyline") (90 . 3) (70 . 0)
(43 . 0.0) (10 2047.5113122172 1131.221719457) (10 2047.3630090498 1153.8392533937) (10 2043.7408371041
1161.3885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2119.1550904978 1153.8461538462 0.0) (10 2109.8911292936 1187.159811998 0.0) (10 2065.8200163147
1170.6115775927 0.0) (10 2043.7408371041 1161.3885746606 0.0))
((0 . "LWPOLYLINE") (100 . "AcDbEntity") (8 . "PLANTS") (62 . 94) (370 . 13) (100 . "AcDbPolyline") (90 . 3) (70 . 0)
(43 . 0.0) (10 2066.3652714932 1097.2850678733) (10 2054.0031674208 1127.2966063348) (10 2047.5113122172
1131.221719457))
((0 . "LWPOLYLINE") (100 . "AcDbEntity") (8 . "PLANTS") (62 . 94) (370 . 13) (100 . "AcDbPolyline") (90 . 2) (70 . 0)
(43 . 0.0) (10 2051.2817873303 3672.6994343891) (10 2081.4479638009 3665.1583710407))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2051.2817873303 3672.6994343891 0.0) (10 2043.4988875606 3708.3287138312 0.0) (10 2075.6459799719
3685.2456456166 0.0) (10 2085.218438914 3702.8661764706 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2119.1550904977 3559.5779411765 0.0) (10 2088.1270127802 3568.5396935129 0.0) (10 2081.2400467461
3528.8199091782 0.0) (10 2051.2817873303 3533.182239819 0.0))
((0 . "LWPOLYLINE") (100 . "AcDbEntity") (8 . "PLANTS") (62 . 94) (370 . 13) (100 . "AcDbPolyline") (90 . 2) (70 . 0)
(43 . 0.0) (10 2066.3652714932 1097.2850678733) (10 2051.2817873303 1089.7426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2100.3019230769 3495.4751131222 0.0) (10 2102.748836644 3464.7928650647 0.0) (10 2033.0330433348
3458.0948253275 0.0) (10 2055.0530542986 3495.4751131222 0.0))
((0 . "LWPOLYLINE") (100 . "AcDbEntity") (8 . "PLANTS") (62 . 94) (370 . 13) (100 . "AcDbPolyline") (90 . 2) (70 . 0)
(43 . 0.0) (10 2062.5940045249 3363.4989819005) (10 2077.6774886878 3374.811199095))
((0 . "LWPOLYLINE") (100 . "AcDbEntity") (8 . "PLANTS") (62 . 94) (370 . 13) (100 . "AcDbPolyline") (90 . 3) (70 . 0)
(43 . 0.0) (10 2066.3652714932 1097.2850678733) (10 2119.1550904977 1097.1373303167) (10 2134.2385746606
1093.5152714932))
((0 . "LWPOLYLINE") (100 . "AcDbEntity") (8 . "PLANTS") (62 . 94) (370 . 13) (100 . "AcDbPolyline") (90 . 2) (70 . 0)
(43 . 0.0) (10 2111.6141402715 3371.0407239819) (10 2077.6774886878 3374.811199095))
((0 . "LWPOLYLINE") (100 . "AcDbEntity") (8 . "PLANTS") (62 . 94) (370 . 13) (100 . "AcDbPolyline") (90 . 3) (70 . 0)
(43 . 0.0) (10 2092.7601809955 3408.7478506787) (10 2078.7334841629 3389.8946832579) (10 2077.6774886878
3374.811199095))
((0 . "LWPOLYLINE") (100 . "AcDbEntity") (8 . "PLANTS") (62 . 94) (370 . 13) (100 . "AcDbPolyline") (90 . 2) (70 . 0)
(43 . 0.0) (10 2081.4479638009 3631.221719457) (10 2081.4479638009 3665.1583710407))
((0 . "LWPOLYLINE") (100 . "AcDbEntity") (8 . "PLANTS") (62 . 94) (370 . 13) (100 . "AcDbPolyline") (90 . 2) (70 . 0)
(43 . 0.0) (10 2081.4479638009 3665.1583710407) (10 2085.218438914 3672.6994343891))
((0 . "LWPOLYLINE") (100 . "AcDbEntity") (8 . "PLANTS") (62 . 94) (370 . 13) (100 . "AcDbPolyline") (90 . 3) (70 . 0)
(43 . 0.0) (10 2081.4479638009 3631.221719457) (10 2096.5306561086 3623.8346153846) (10 2111.6141402715
3623.6806561086))
((0 . "LWPOLYLINE") (100 . "AcDbEntity") (8 . "PLANTS") (62 . 94) (370 . 13) (100 . "AcDbPolyline") (90 . 3) (70 . 0)
(43 . 0.0) (10 2085.218438914 3733.0316742081) (10 2078.8817873303 3721.7194570136) (10 2085.218438914 3702.8661764706))
((0 . "LWPOLYLINE") (100 . "AcDbEntity") (8 . "PLANTS") (62 . 94) (370 . 13) (100 . "AcDbPolyline") (90 . 3) (70 . 0)
(43 . 0.0) (10 2130.4673076923 3717.9483031674) (10 2107.8428733032 3703.9222850679) (10 2085.218438914
3702.8661764706))
((0 . "LWPOLYLINE") (100 . "AcDbEntity") (8 . "PLANTS") (62 . 94) (370 . 13) (100 . "AcDbPolyline") (90 . 2) (70 . 0)
(43 . 0.0) (10 2100.3019230769 3495.4751131222) (10 2085.218438914 3506.7873303167))
((0 . "LWPOLYLINE") (100 . "AcDbEntity") (8 . "PLANTS") (62 . 94) (370 . 13) (100 . "AcDbPolyline") (90 . 2) (70 . 0)
(43 . 0.0) (10 2092.7601809955 3408.7478506787) (10 2092.7601809955 3420.0600678733))
((0 . "LWPOLYLINE") (100 . "AcDbEntity") (8 . "PLANTS") (62 . 94) (370 . 13) (100 . "AcDbPolyline") (90 . 2) (70 . 0)
(43 . 0.0) (10 2092.7601809955 3408.7478506787) (10 2122.9263574661 3404.9773755656))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2111.6141402715 3793.3639140271 0.0) (10 2089.4800483906 3801.6244368197 0.0) (10 2101.1795373115
3839.4964551918 0.0) (10 2096.5306561086 3853.6949095023 0.0))
((0 . "LWPOLYLINE") (100 . "AcDbEntity") (8 . "PLANTS") (62 . 94) (370 . 13) (100 . "AcDbPolyline") (90 . 3) (70 . 0)
(43 . 0.0) (10 2096.5306561086 3853.6949095023) (10 2111.6141402715 3860.1805429864) (10 2126.6968325792
3861.2372171946))
((0 . "LWPOLYLINE") (100 . "AcDbEntity") (8 . "PLANTS") (62 . 94) (370 . 13) (100 . "AcDbPolyline") (90 . 3) (70 . 0)
(43 . 0.0) (10 2111.6141402715 3231.5236425339) (10 2103.7106334842 3209.2678733032) (10 2100.0650267272
3209.0806849428))
((0 . "LWPOLYLINE") (100 . "AcDbEntity") (8 . "PLANTS") (62 . 94) (370 . 13) (100 . "AcDbPolyline") (90 . 2) (70 . 0)
(43 . 0.0) (10 2100.3019230769 3495.4751131222) (10 2119.1550904977 3495.4751131222))
((0 . "LWPOLYLINE") (100 . "AcDbEntity") (8 . "PLANTS") (62 . 94) (370 . 13) (100 . "AcDbPolyline") (90 . 3) (70 . 0)
(43 . 0.0) (10 2119.1550904977 1153.8461538462) (10 2107.8432126697 1143.738800905) (10 2100.3019230769
1142.5339366516))
((0 . "LWPOLYLINE") (100 . "AcDbEntity") (8 . "PLANTS") (62 . 94) (370 . 13) (100 . "AcDbPolyline") (90 . 3) (70 . 0)
(43 . 0.0) (10 2141.7795248869 3959.2760180995) (10 2122.9263574661 3976.9254524887) (10 2104.07239819 3981.9004524887))
((0 . "LWPOLYLINE") (100 . "AcDbEntity") (8 . "PLANTS") (62 . 94) (370 . 13) (100 . "AcDbPolyline") (90 . 3) (70 . 0)
(43 . 0.0) (10 2104.07239819 931.3716063348) (10 2100.4563348416 889.895361991) (10 2111.6141402715 874.810520362))
((0 . "LWPOLYLINE") (100 . "AcDbEntity") (8 . "PLANTS") (62 . 94) (370 . 13) (100 . "AcDbPolyline") (90 . 2) (70 . 0)
(43 . 0.0) (10 2104.07239819 931.3716063348) (10 2111.6141402715 935.1442307692))
((0 . "LWPOLYLINE") (100 . "AcDbEntity") (8 . "PLANTS") (62 . 94) (370 . 13) (100 . "AcDbPolyline") (90 . 3) (70 . 0)
(43 . 0.0) (10 2107.8428733032 1025.6419683258) (10 2130.0992081448 1006.5726244344) (10 2130.4673076923
991.7053167421))
((0 . "LWPOLYLINE") (100 . "AcDbEntity") (8 . "PLANTS") (62 . 94) (370 . 13) (100 . "AcDbPolyline") (90 . 3) (70 . 0)
(43 . 0.0) (10 2107.8428733032 1025.6419683258) (10 2112.8116515837 1040.7239819005) (10 2134.2385746606
1067.1182126697))
((0 . "LWPOLYLINE") (100 . "AcDbEntity") (8 . "PLANTS") (62 . 94) (370 . 13) (100 . "AcDbPolyline") (90 . 2) (70 . 0)
(43 . 0.0) (10 2111.6141402715 3770.739479638) (10 2111.6141402715 3793.3639140271))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2111.6141402715 3793.3639140271 0.0) (10 2147.9210127174 3796.9430526884 0.0) (10 2149.5930928018
3836.1269682568 0.0) (10 2141.7795248869 3861.2372171946 0.0))
((0 . "LWPOLYLINE") (100 . "AcDbEntity") (8 . "PLANTS") (62 . 94) (370 . 13) (100 . "AcDbPolyline") (90 . 2) (70 . 0)
(43 . 0.0) (10 2111.6141402715 3770.739479638) (10 2130.4673076923 3770.739479638))
((0 . "LWPOLYLINE") (100 . "AcDbEntity") (8 . "PLANTS") (62 . 94) (370 . 13) (100 . "AcDbPolyline") (90 . 2) (70 . 0)
(43 . 0.0) (10 2126.6968325792 3612.367760181) (10 2111.6141402715 3623.6806561086))
((0 . "LWPOLYLINE") (100 . "AcDbEntity") (8 . "PLANTS") (62 . 94) (370 . 13) (100 . "AcDbPolyline") (90 . 2) (70 . 0)
(43 . 0.0) (10 2122.9263574661 3661.3872171946) (10 2111.6141402715 3623.6806561086))
((0 . "LWPOLYLINE") (100 . "AcDbEntity") (8 . "PLANTS") (62 . 94) (370 . 13) (100 . "AcDbPolyline") (90 . 3) (70 . 0)
(43 . 0.0) (10 2111.6141402715 3371.0407239819) (10 2122.9197963801 3360.9326923077) (10 2130.4673076923
3359.7285067873))
((0 . "LWPOLYLINE") (100 . "AcDbEntity") (8 . "PLANTS") (62 . 94) (370 . 13) (100 . "AcDbPolyline") (90 . 2) (70 . 0)
(43 . 0.0) (10 2111.6141402715 3371.0407239819) (10 2122.9263574661 3404.9773755656))
((0 . "LWPOLYLINE") (100 . "AcDbEntity") (8 . "PLANTS") (62 . 94) (370 . 13) (100 . "AcDbPolyline") (90 . 3) (70 . 0)
(43 . 0.0) (10 2119.1550904977 969.0808823529) (10 2111.7619909502 953.996040724) (10 2111.6141402715 935.1442307692))
((0 . "LWPOLYLINE") (100 . "AcDbEntity") (8 . "PLANTS") (62 . 94) (370 . 13) (100 . "AcDbPolyline") (90 . 3) (70 . 0)
(43 . 0.0) (10 2168.1752262443 935.1442307692) (10 2153.0917420814 938.9071266968) (10 2111.6141402715 935.1442307692))
((0 . "LWPOLYLINE") (100 . "AcDbEntity") (8 . "PLANTS") (62 . 94) (370 . 13) (100 . "AcDbPolyline") (90 . 2) (70 . 0)
(43 . 0.0) (10 2111.6141402715 874.810520362) (10 2156.8630090498 871.0407239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2134.2385746606 818.2494343891 0.0) (10 2083.3875947962 791.2486081017 0.0) (10 2083.7220908891
857.8252895404 0.0) (10 2111.6141402715 874.810520362 0.0))
((0 . "LWPOLYLINE") (100 . "AcDbEntity") (8 . "PLANTS") (62 . 94) (370 . 13) (100 . "AcDbPolyline") (90 . 2) (70 . 0)
(43 . 0.0) (10 2122.9263574661 3661.3872171946) (10 2119.1550904977 3672.6994343891))
((0 . "LWPOLYLINE") (100 . "AcDbEntity") (8 . "PLANTS") (62 . 94) (370 . 13) (100 . "AcDbPolyline") (90 . 2) (70 . 0)
(43 . 0.0) (10 2119.1550904977 3559.5779411765) (10 2126.6968325792 3536.9535067873))
((0 . "LWPOLYLINE") (100 . "AcDbEntity") (8 . "PLANTS") (62 . 94) (370 . 13) (100 . "AcDbPolyline") (90 . 2) (70 . 0)
(43 . 0.0) (10 2119.1550904977 3559.5779411765) (10 2126.6968325792 3612.367760181))
((0 . "LWPOLYLINE") (100 . "AcDbEntity") (8 . "PLANTS") (62 . 94) (370 . 13) (100 . "AcDbPolyline") (90 . 3) (70 . 0)
(43 . 0.0) (10 2126.6968325792 3480.3924208145) (10 2126.6968325792 3487.9333710407) (10 2119.1550904977
3495.4751131222))
((0 . "LWPOLYLINE") (100 . "AcDbEntity") (8 . "PLANTS") (62 . 94) (370 . 13) (100 . "AcDbPolyline") (90 . 2) (70 . 0)
(43 . 0.0) (10 2126.6968325792 3536.9535067873) (10 2119.1550904977 3495.4751131222))
((0 . "LWPOLYLINE") (100 . "AcDbEntity") (8 . "PLANTS") (62 . 94) (370 . 13) (100 . "AcDbPolyline") (90 . 2) (70 . 0)
(43 . 0.0) (10 2122.9263574661 3156.1085972851) (10 2119.1550904977 3144.7963800905))
((0 . "LWPOLYLINE") (100 . "AcDbEntity") (8 . "PLANTS") (62 . 94) (370 . 13) (100 . "AcDbPolyline") (90 . 2) (70 . 0)
(43 . 0.0) (10 2119.1550904977 1153.8461538462) (10 2164.403959276 1150.0763574661))
((0 . "LWPOLYLINE") (100 . "AcDbEntity") (8 . "PLANTS") (62 . 94) (370 . 13) (100 . "AcDbPolyline") (90 . 2) (70 . 0)
(43 . 0.0) (10 2141.7795248869 3665.1583710407) (10 2122.9263574661 3661.3872171946))
((0 . "LWPOLYLINE") (100 . "AcDbEntity") (8 . "PLANTS") (62 . 94) (370 . 13) (100 . "AcDbPolyline") (90 . 2) (70 . 0)
(43 . 0.0) (10 2130.4673076923 3412.5191176471) (10 2122.9263574661 3404.9773755656))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2124.811199095 3301.2817873303 0.0) (10 2106.2775431575 3267.1401823459 0.0) (10 2162.5908469214
3247.631095338 0.0) (10 2145.5507918552 3216.440158371 0.0))
((0 . "LWPOLYLINE") (100 . "AcDbEntity") (8 . "PLANTS") (62 . 94) (370 . 13) (100 . "AcDbPolyline") (90 . 2) (70 . 0)
(43 . 0.0) (10 2124.811199095 3301.2817873303) (10 2130.4673076923 3359.7285067873))
((0 . "LWPOLYLINE") (100 . "AcDbEntity") (8 . "PLANTS") (62 . 94) (370 . 13) (100 . "AcDbPolyline") (90 . 2) (70 . 0)
(43 . 0.0) (10 2168.1752262443 3303.1674208145) (10 2124.811199095 3301.2817873303))
((0 . "LWPOLYLINE") (100 . "AcDbEntity") (8 . "PLANTS") (62 . 94) (370 . 13) (100 . "AcDbPolyline") (90 . 2) (70 . 0)
(43 . 0.0) (10 2126.6968325792 3906.4860859729) (10 2126.6968325792 3861.2372171946))
((0 . "LWPOLYLINE") (100 . "AcDbEntity") (8 . "PLANTS") (62 . 94) (370 . 13) (100 . "AcDbPolyline") (90 . 3) (70 . 0)
(43 . 0.0) (10 2149.3212669683 3947.963800905) (10 2136.9530542986 3914.0333710407) (10 2126.6968325792
3906.4860859729))
((0 . "LWPOLYLINE") (100 . "AcDbEntity") (8 . "PLANTS") (62 . 94) (370 . 13) (100 . "AcDbPolyline") (90 . 2) (70 . 0)
(43 . 0.0) (10 2141.7795248869 3861.2372171946) (10 2126.6968325792 3861.2372171946))
((0 . "LWPOLYLINE") (100 . "AcDbEntity") (8 . "PLANTS") (62 . 94) (370 . 13) (100 . "AcDbPolyline") (90 . 2) (70 . 0)
(43 . 0.0) (10 2153.0917420814 3627.4505656109) (10 2126.6968325792 3612.367760181))
((0 . "LWPOLYLINE") (100 . "AcDbEntity") (8 . "PLANTS") (62 . 94) (370 . 13) (100 . "AcDbPolyline") (90 . 2) (70 . 0)
(43 . 0.0) (10 2126.6968325792 3536.9535067873) (10 2153.0917420814 3540.7239819005))
((0 . "LWPOLYLINE") (100 . "AcDbEntity") (8 . "PLANTS") (62 . 94) (370 . 13) (100 . "AcDbPolyline") (90 . 2) (70 . 0)
(43 . 0.0) (10 2126.6968325792 3480.3924208145) (10 2160.6334841629 3480.3924208145))
((0 . "LWPOLYLINE") (100 . "AcDbEntity") (8 . "PLANTS") (62 . 94) (370 . 13) (100 . "AcDbPolyline") (90 . 3) (70 . 0)
(43 . 0.0) (10 2130.4673076923 3412.5191176471) (10 2123.0807692308 3442.6845022624) (10 2126.6968325792
3480.3924208145))
((0 . "LWPOLYLINE") (100 . "AcDbEntity") (8 . "PLANTS") (62 . 94) (370 . 13) (100 . "AcDbPolyline") (90 . 3) (70 . 0)
(43 . 0.0) (10 2164.403959276 3996.9838235294) (10 2136.9530542986 4095.0226244344) (10 2122.4365125948
4122.4743078653))
((0 . "LWPOLYLINE") (100 . "AcDbEntity") (8 . "PLANTS") (62 . 94) (370 . 13) (100 . "AcDbPolyline") (90 . 2) (70 . 0)
(43 . 0.0) (10 2065.0279650009 4056.8645391865) (10 2130.4673076923 4008.296040724))
((0 . "LWPOLYLINE") (100 . "AcDbEntity") (8 . "PLANTS") (62 . 94) (370 . 13) (100 . "AcDbPolyline") (90 . 2) (70 . 0)
(43 . 0.0) (10 2145.5507918552 3733.0316742081) (10 2130.4673076923 3770.739479638))
((0 . "LWPOLYLINE") (100 . "AcDbEntity") (8 . "PLANTS") (62 . 94) (370 . 13) (100 . "AcDbPolyline") (90 . 2) (70 . 0)
(43 . 0.0) (10 2183.257918552 3778.2805429864) (10 2130.4673076923 3770.739479638))
((0 . "LWPOLYLINE") (100 . "AcDbEntity") (8 . "PLANTS") (62 . 94) (370 . 13) (100 . "AcDbPolyline") (90 . 2) (70 . 0)
(43 . 0.0) (10 2130.4673076923 3717.9483031674) (10 2145.5507918552 3695.3238687783))
((0 . "LWPOLYLINE") (100 . "AcDbEntity") (8 . "PLANTS") (62 . 94) (370 . 13) (100 . "AcDbPolyline") (90 . 2) (70 . 0)
(43 . 0.0) (10 2130.4673076923 3717.9483031674) (10 2145.5507918552 3733.0316742081))
((0 . "LWPOLYLINE") (100 . "AcDbEntity") (8 . "PLANTS") (62 . 94) (370 . 13) (100 . "AcDbPolyline") (90 . 2) (70 . 0)
(43 . 0.0) (10 2130.4673076923 3412.5191176471) (10 2156.8630090498 3416.2895927602))
((0 . "LWPOLYLINE") (100 . "AcDbEntity") (8 . "PLANTS") (62 . 94) (370 . 13) (100 . "AcDbPolyline") (90 . 3) (70 . 0)
(43 . 0.0) (10 2168.1752262443 3389.8946832579) (10 2149.1729638009 3368.3265837104) (10 2130.4673076923
3359.7285067873))
((0 . "LWPOLYLINE") (100 . "AcDbEntity") (8 . "PLANTS") (62 . 94) (370 . 13) (100 . "AcDbPolyline") (90 . 2) (70 . 0)
(43 . 0.0) (10 2138.0090497738 641.0265837104) (10 2130.4673076923 637.253959276))
((0 . "LWPOLYLINE") (100 . "AcDbEntity") (8 . "PLANTS") (62 . 94) (370 . 13) (100 . "AcDbPolyline") (90 . 2) (70 . 0)
(43 . 0.0) (10 2134.2385746606 1093.5152714932) (10 2134.2385746606 1067.1182126697))
((0 . "LWPOLYLINE") (100 . "AcDbEntity") (8 . "PLANTS") (62 . 94) (370 . 13) (100 . "AcDbPolyline") (90 . 3) (70 . 0)
(43 . 0.0) (10 2171.9457013575 1138.7641402715) (10 2156.7147058824 1116.1397058824) (10 2134.2385746606
1093.5152714932))
((0 . "LWPOLYLINE") (100 . "AcDbEntity") (8 . "PLANTS") (62 . 94) (370 . 13) (100 . "AcDbPolyline") (90 . 2) (70 . 0)
(43 . 0.0) (10 2134.2385746606 1067.1182126697) (10 2213.4240950226 1070.8908371041))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2171.9457013575 833.3342760181 0.0) (10 2147.3688305484 805.9337896723 0.0) (10 2177.9374165679
758.187277422 0.0) (10 2134.2385746606 742.8365384615 0.0))
((0 . "LWPOLYLINE") (100 . "AcDbEntity") (8 . "PLANTS") (62 . 94) (370 . 13) (100 . "AcDbPolyline") (90 . 2) (70 . 0)
(43 . 0.0) (10 2138.0090497738 663.6510180995) (10 2138.0090497738 641.0265837104))
((0 . "LWPOLYLINE") (100 . "AcDbEntity") (8 . "PLANTS") (62 . 94) (370 . 13) (100 . "AcDbPolyline") (90 . 2) (70 . 0)
(43 . 0.0) (10 2138.0090497738 641.0265837104) (10 2187.0283936652 625.9417420814))
((0 . "LWPOLYLINE") (100 . "AcDbEntity") (8 . "PLANTS") (62 . 94) (370 . 13) (100 . "AcDbPolyline") (90 . 2) (70 . 0)
(43 . 0.0) (10 2141.7795248869 3959.2760180995) (10 2149.3212669683 3959.2760180995))
((0 . "LWPOLYLINE") (100 . "AcDbEntity") (8 . "PLANTS") (62 . 94) (370 . 13) (100 . "AcDbPolyline") (90 . 2) (70 . 0)
(43 . 0.0) (10 2141.7795248869 3861.2372171946) (10 2175.7161764706 3891.4027149321))
((0 . "LWPOLYLINE") (100 . "AcDbEntity") (8 . "PLANTS") (62 . 94) (370 . 13) (100 . "AcDbPolyline") (90 . 2) (70 . 0)
(43 . 0.0) (10 2141.7795248869 3665.1583710407) (10 2153.0917420814 3653.8461538462))
((0 . "LWPOLYLINE") (100 . "AcDbEntity") (8 . "PLANTS") (62 . 94) (370 . 13) (100 . "AcDbPolyline") (90 . 3) (70 . 0)
(43 . 0.0) (10 2141.7795248869 3665.1583710407) (10 2145.4024886878 3672.7063348416) (10 2145.5507918552
3695.3238687783))
((0 . "LWPOLYLINE") (100 . "AcDbEntity") (8 . "PLANTS") (62 . 94) (370 . 13) (100 . "AcDbPolyline") (90 . 2) (70 . 0)
(43 . 0.0) (10 2175.7161764706 3717.9483031674) (10 2145.5507918552 3733.0316742081))
((0 . "LWPOLYLINE") (100 . "AcDbEntity") (8 . "PLANTS") (62 . 94) (370 . 13) (100 . "AcDbPolyline") (90 . 2) (70 . 0)
(43 . 0.0) (10 2145.5507918552 3695.3238687783) (10 2175.7161764706 3702.8661764706))
((0 . "LWPOLYLINE") (100 . "AcDbEntity") (8 . "PLANTS") (62 . 94) (370 . 13) (100 . "AcDbPolyline") (90 . 2) (70 . 0)
(43 . 0.0) (10 2149.3212669683 3947.963800905) (10 2149.3212669683 3959.2760180995))
((0 . "LWPOLYLINE") (100 . "AcDbEntity") (8 . "PLANTS") (62 . 94) (370 . 13) (100 . "AcDbPolyline") (90 . 3) (70 . 0)
(43 . 0.0) (10 2164.403959276 3996.9838235294) (10 2163.1996606335 3974.3593891403) (10 2149.3212669683
3959.2760180995))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2149.3212669683 3947.963800905 0.0) (10 2188.9339320028 3964.6769647262 0.0) (10 2225.8130851356
3930.7092751917 0.0) (10 2266.2139140271 3947.963800905 0.0))
((0 . "LWPOLYLINE") (100 . "AcDbEntity") (8 . "PLANTS") (62 . 94) (370 . 13) (100 . "AcDbPolyline") (90 . 3) (70 . 0)
(43 . 0.0) (10 2183.257918552 580.6928733032) (10 2168.1752262443 579.489479638) (10 2149.3212669683 561.8410633484))
((0 . "LWPOLYLINE") (100 . "AcDbEntity") (8 . "PLANTS") (62 . 94) (370 . 13) (100 . "AcDbPolyline") (90 . 3) (70 . 0)
(43 . 0.0) (10 2160.6334841629 4144.0426470588) (10 2160.4786199095 4162.8897058824) (10 2159.0643469597
4164.3346899966))
((0 . "LWPOLYLINE") (100 . "AcDbEntity") (8 . "PLANTS") (62 . 94) (370 . 13) (100 . "AcDbPolyline") (90 . 2) (70 . 0)
(43 . 0.0) (10 2160.6334841629 4144.0426470588) (10 2146.6469631274 4150.1433941883))
((0 . "LWPOLYLINE") (100 . "AcDbEntity") (8 . "PLANTS") (62 . 94) (370 . 13) (100 . "AcDbPolyline") (90 . 2) (70 . 0)
(43 . 0.0) (10 2153.0917420814 3653.8461538462) (10 2153.0917420814 3627.4505656109))
((0 . "LWPOLYLINE") (100 . "AcDbEntity") (8 . "PLANTS") (62 . 94) (370 . 13) (100 . "AcDbPolyline") (90 . 3) (70 . 0)
(43 . 0.0) (10 2153.0917420814 3653.8461538462) (10 2175.7196832579 3653.99739819) (10 2188.9140271493 3659.5022624434))
((0 . "LWPOLYLINE") (100 . "AcDbEntity") (8 . "PLANTS") (62 . 94) (370 . 13) (100 . "AcDbPolyline") (90 . 2) (70 . 0)
(43 . 0.0) (10 2179.4874434389 3623.6806561086) (10 2153.0917420814 3627.4505656109))
((0 . "LWPOLYLINE") (100 . "AcDbEntity") (8 . "PLANTS") (62 . 94) (370 . 13) (100 . "AcDbPolyline") (90 . 3) (70 . 0)
(43 . 0.0) (10 2168.1752262443 3389.8946832579) (10 2163.2130090498 3412.364479638) (10 2156.8630090498
3416.2895927602))
((0 . "LWPOLYLINE") (100 . "AcDbEntity") (8 . "PLANTS") (62 . 94) (370 . 13) (100 . "AcDbPolyline") (90 . 3) (70 . 0)
(43 . 0.0) (10 2156.8630090498 3416.2895927602) (10 2149.4695701357 3450.2262443439) (10 2160.6334841629
3480.3924208145))
((0 . "LWPOLYLINE") (100 . "AcDbEntity") (8 . "PLANTS") (62 . 94) (370 . 13) (100 . "AcDbPolyline") (90 . 3) (70 . 0)
(43 . 0.0) (10 2156.8630090498 976.6204751131) (10 2168.1686651584 975.0980769231) (10 2175.7161764706 980.3930995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2171.9457013575 833.3342760181 0.0) (10 2174.6370634663 849.8856004549 0.0) (10 2152.2573645831
854.6321443639 0.0) (10 2156.8630090498 871.0407239819 0.0))
((0 . "LWPOLYLINE") (100 . "AcDbEntity") (8 . "PLANTS") (62 . 94) (370 . 13) (100 . "AcDbPolyline") (90 . 2) (70 . 0)
(43 . 0.0) (10 2156.8630090498 871.0407239819) (10 2171.9457013575 882.3529411765))
((0 . "LWPOLYLINE") (100 . "AcDbEntity") (8 . "PLANTS") (62 . 94) (370 . 13) (100 . "AcDbPolyline") (90 . 3) (70 . 0)
(43 . 0.0) (10 2160.6334841629 4144.0426470588) (10 2171.9457013575 4130.163800905) (10 2205.8823529412
4125.1881221719))
((0 . "LWPOLYLINE") (100 . "AcDbEntity") (8 . "PLANTS") (62 . 94) (370 . 13) (100 . "AcDbPolyline") (90 . 2) (70 . 0)
(43 . 0.0) (10 2164.403959276 3491.7046380091) (10 2160.6334841629 3480.3924208145))
((0 . "LWPOLYLINE") (100 . "AcDbEntity") (8 . "PLANTS") (62 . 94) (370 . 13) (100 . "AcDbPolyline") (90 . 3) (70 . 0)
(43 . 0.0) (10 2160.6334841629 1327.2992081448) (10 2179.4874434389 1313.4220588235) (10 2209.6528280543 1308.44739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2164.403959276 3996.9838235294 0.0) (10 2185.9547334376 3996.2164599725 0.0) (10 2192.0602784565
4025.591227824 0.0) (10 2217.1945701357 4015.8371040724 0.0))
((0 . "LWPOLYLINE") (100 . "AcDbEntity") (8 . "PLANTS") (62 . 94) (370 . 13) (100 . "AcDbPolyline") (90 . 2) (70 . 0)
(43 . 0.0) (10 2168.1752262443 3303.1674208145) (10 2164.403959276 3325.7918552036))
((0 . "LWPOLYLINE") (100 . "AcDbEntity") (8 . "PLANTS") (62 . 94) (370 . 13) (100 . "AcDbPolyline") (90 . 2) (70 . 0)
(43 . 0.0) (10 2164.403959276 1150.0763574661) (10 2171.9457013575 1138.7641402715))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2164.403959276 1150.0763574661 0.0) (10 2153.1153692574 1194.2473329248 0.0) (10 2124.4103536282
1231.084699133 0.0) (10 2099.2189843781 1267.8856912609 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2132.6716656837 1306.1173270387 0.0) (10 2165.9312046487 1278.2284396591 0.0) (10 2152.9120468833
1229.3749623925 0.0) (10 2175.7161764706 1195.3252262443 0.0))
((0 . "LWPOLYLINE") (100 . "AcDbEntity") (8 . "PLANTS") (62 . 94) (370 . 13) (100 . "AcDbPolyline") (90 . 3) (70 . 0)
(43 . 0.0) (10 2168.1752262443 3389.8946832579) (10 2182.0533936652 3378.5824660633) (10 2179.4874434389
3359.7285067873))
((0 . "LWPOLYLINE") (100 . "AcDbEntity") (8 . "PLANTS") (62 . 94) (370 . 13) (100 . "AcDbPolyline") (90 . 3) (70 . 0)
(43 . 0.0) (10 2268.529067986 3299.3999025612) (10 2179.4874434389 3299.4031674208) (10 2168.1752262443
3303.1674208145))
((0 . "LWPOLYLINE") (100 . "AcDbEntity") (8 . "PLANTS") (62 . 94) (370 . 13) (100 . "AcDbPolyline") (90 . 3) (70 . 0)
(43 . 0.0) (10 2168.1752262443 935.1442307692) (10 2168.3230769231 893.665158371) (10 2171.9457013575 882.3529411765))
((0 . "LWPOLYLINE") (100 . "AcDbEntity") (8 . "PLANTS") (62 . 94) (370 . 13) (100 . "AcDbPolyline") (90 . 2) (70 . 0)
(43 . 0.0) (10 2198.3406108597 938.9140271493) (10 2168.1752262443 935.1442307692))
((0 . "LWPOLYLINE") (100 . "AcDbEntity") (8 . "PLANTS") (62 . 94) (370 . 13) (100 . "AcDbPolyline") (90 . 2) (70 . 0)
(43 . 0.0) (10 2220.9650452489 1150.0763574661) (10 2171.9457013575 1138.7641402715))
((0 . "LWPOLYLINE") (100 . "AcDbEntity") (8 . "PLANTS") (62 . 94) (370 . 13) (100 . "AcDbPolyline") (90 . 2) (70 . 0)
(43 . 0.0) (10 2209.6528280543 878.5831447964) (10 2171.9457013575 882.3529411765))
((0 . "LWPOLYLINE") (100 . "AcDbEntity") (8 . "PLANTS") (62 . 94) (370 . 13) (100 . "AcDbPolyline") (90 . 2) (70 . 0)
(43 . 0.0) (10 2171.9457013575 833.3342760181) (10 2213.4240950226 833.3342760181))
((0 . "LWPOLYLINE") (100 . "AcDbEntity") (8 . "PLANTS") (62 . 94) (370 . 13) (100 . "AcDbPolyline") (90 . 2) (70 . 0)
(43 . 0.0) (10 2190.7996606335 682.5028280543) (10 2171.9457013575 686.2754524887))
((0 . "LWPOLYLINE") (100 . "AcDbEntity") (8 . "PLANTS") (62 . 94) (370 . 13) (100 . "AcDbPolyline") (90 . 2) (70 . 0)
(43 . 0.0) (10 2175.7161764706 3717.9483031674) (10 2175.7161764706 3702.8661764706))
((0 . "LWPOLYLINE") (100 . "AcDbEntity") (8 . "PLANTS") (62 . 94) (370 . 13) (100 . "AcDbPolyline") (90 . 2) (70 . 0)
(43 . 0.0) (10 2200.2262443439 3731.146719457) (10 2175.7161764706 3717.9483031674))
((0 . "LWPOLYLINE") (100 . "AcDbEntity") (8 . "PLANTS") (62 . 94) (370 . 13) (100 . "AcDbPolyline") (90 . 3) (70 . 0)
(43 . 0.0) (10 2175.7161764706 3702.8661764706) (10 2189.595361991 3687.7828054299) (10 2188.9140271493
3659.5022624434))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2179.4874434389 3623.6806561086 0.0) (10 2182.6954666108 3591.0128655492 0.0) (10 2227.5450641387
3581.0747723986 0.0) (10 2213.4240950226 3542.6096153846 0.0))
((0 . "LWPOLYLINE") (100 . "AcDbEntity") (8 . "PLANTS") (62 . 94) (370 . 13) (100 . "AcDbPolyline") (90 . 2) (70 . 0)
(43 . 0.0) (10 2179.4874434389 3623.6806561086) (10 2188.9140271493 3659.5022624434))
((0 . "LWPOLYLINE") (100 . "AcDbEntity") (8 . "PLANTS") (62 . 94) (370 . 13) (100 . "AcDbPolyline") (90 . 3) (70 . 0)
(43 . 0.0) (10 2200.2262443439 3731.146719457) (10 2184.4556561086 3766.9683257919) (10 2183.257918552 3778.2805429864))
((0 . "LWPOLYLINE") (100 . "AcDbEntity") (8 . "PLANTS") (62 . 94) (370 . 13) (100 . "AcDbPolyline") (90 . 2) (70 . 0)
(43 . 0.0) (10 2183.257918552 3778.2805429864) (10 2198.3406108597 3785.8216063348))
((0 . "LWPOLYLINE") (100 . "AcDbEntity") (8 . "PLANTS") (62 . 94) (370 . 13) (100 . "AcDbPolyline") (90 . 2) (70 . 0)
(43 . 0.0) (10 2183.257918552 580.6928733032) (10 2202.1118778281 576.9230769231))
((0 . "LWPOLYLINE") (100 . "AcDbEntity") (8 . "PLANTS") (62 . 94) (370 . 13) (100 . "AcDbPolyline") (90 . 2) (70 . 0)
(43 . 0.0) (10 2183.257918552 580.6928733032) (10 2187.0283936652 625.9417420814))
((0 . "LWPOLYLINE") (100 . "AcDbEntity") (8 . "PLANTS") (62 . 94) (370 . 13) (100 . "AcDbPolyline") (90 . 3) (70 . 0)
(43 . 0.0) (10 2209.6528280543 1257.5424208145) (10 2190.9540723982 1268.017760181) (10 2187.0283936652
1274.5107466063))
((0 . "LWPOLYLINE") (100 . "AcDbEntity") (8 . "PLANTS") (62 . 94) (370 . 13) (100 . "AcDbPolyline") (90 . 2) (70 . 0)
(43 . 0.0) (10 2187.0283936652 1014.3297511312) (10 2207.7679864253 1016.2132352941))
((0 . "LWPOLYLINE") (100 . "AcDbEntity") (8 . "PLANTS") (62 . 94) (370 . 13) (100 . "AcDbPolyline") (90 . 2) (70 . 0)
(43 . 0.0) (10 2194.5701357466 629.7143665158) (10 2187.0283936652 625.9417420814))
((0 . "LWPOLYLINE") (100 . "AcDbEntity") (8 . "PLANTS") (62 . 94) (370 . 13) (100 . "AcDbPolyline") (90 . 3) (70 . 0)
(43 . 0.0) (10 2232.2772624434 3634.9928733032) (10 2198.2735294118 3660.1157239819) (10 2188.9140271493
3659.5022624434))
((0 . "LWPOLYLINE") (100 . "AcDbEntity") (8 . "PLANTS") (62 . 94) (370 . 13) (100 . "AcDbPolyline") (90 . 2) (70 . 0)
(43 . 0.0) (10 2190.7996606335 720.2121040724) (10 2194.5701357466 693.8150452489))
((0 . "LWPOLYLINE") (100 . "AcDbEntity") (8 . "PLANTS") (62 . 94) (370 . 13) (100 . "AcDbPolyline") (90 . 2) (70 . 0)
(43 . 0.0) (10 2190.7996606335 682.5028280543) (10 2194.5701357466 629.7143665158))
((0 . "LWPOLYLINE") (100 . "AcDbEntity") (8 . "PLANTS") (62 . 94) (370 . 13) (100 . "AcDbPolyline") (90 . 2) (70 . 0)
(43 . 0.0) (10 2190.7996606335 682.5028280543) (10 2194.5701357466 693.8150452489))
((0 . "LWPOLYLINE") (100 . "AcDbEntity") (8 . "PLANTS") (62 . 94) (370 . 13) (100 . "AcDbPolyline") (90 . 3) (70 . 0)
(43 . 0.0) (10 2224.7363122172 475.1131221719) (10 2202.2597285068 467.4174208145) (10 2190.7996606335 444.9462669683))
((0 . "LWPOLYLINE") (100 . "AcDbEntity") (8 . "PLANTS") (62 . 94) (370 . 13) (100 . "AcDbPolyline") (90 . 2) (70 . 0)
(43 . 0.0) (10 2213.4240950226 3542.6096153846) (10 2194.5701357466 3536.9535067873))
((0 . "LWPOLYLINE") (100 . "AcDbEntity") (8 . "PLANTS") (62 . 94) (370 . 13) (100 . "AcDbPolyline") (90 . 3) (70 . 0)
(43 . 0.0) (10 2202.1118778281 757.9185520362) (10 2198.3406108597 757.9185520362) (10 2194.5701357466 746.6063348416))
((0 . "LWPOLYLINE") (100 . "AcDbEntity") (8 . "PLANTS") (62 . 94) (370 . 13) (100 . "AcDbPolyline") (90 . 2) (70 . 0)
(43 . 0.0) (10 2245.4751131222 695.7013574661) (10 2194.5701357466 693.8150452489))
((0 . "LWPOLYLINE") (100 . "AcDbEntity") (8 . "PLANTS") (62 . 94) (370 . 13) (100 . "AcDbPolyline") (90 . 2) (70 . 0)
(43 . 0.0) (10 2232.2772624434 629.7143665158) (10 2194.5701357466 629.7143665158))
((0 . "LWPOLYLINE") (100 . "AcDbEntity") (8 . "PLANTS") (62 . 94) (370 . 13) (100 . "AcDbPolyline") (90 . 2) (70 . 0)
(43 . 0.0) (10 2232.2772624434 3751.8849547511) (10 2198.3406108597 3785.8216063348))
((0 . "LWPOLYLINE") (100 . "AcDbEntity") (8 . "PLANTS") (62 . 94) (370 . 13) (100 . "AcDbPolyline") (90 . 3) (70 . 0)
(43 . 0.0) (10 2220.9650452489 3834.8416289593) (10 2210.7030542986 3823.5294117647) (10 2198.3406108597
3785.8216063348))
((0 . "LWPOLYLINE") (100 . "AcDbEntity") (8 . "PLANTS") (62 . 94) (370 . 13) (100 . "AcDbPolyline") (90 . 3) (70 . 0)
(43 . 0.0) (10 2228.5067873303 923.8320135747) (10 2209.6531674208 928.7997737557) (10 2198.3406108597 938.9140271493))
((0 . "LWPOLYLINE") (100 . "AcDbEntity") (8 . "PLANTS") (62 . 94) (370 . 13) (100 . "AcDbPolyline") (90 . 2) (70 . 0)
(43 . 0.0) (10 2198.3406108597 938.9140271493) (10 2209.6528280543 961.5384615385))
((0 . "LWPOLYLINE") (100 . "AcDbEntity") (8 . "PLANTS") (62 . 94) (370 . 13) (100 . "AcDbPolyline") (90 . 2) (70 . 0)
(43 . 0.0) (10 2198.3406108597 550.5288461538) (10 2202.1118778281 576.9230769231))
((0 . "LWPOLYLINE") (100 . "AcDbEntity") (8 . "PLANTS") (62 . 94) (370 . 13) (100 . "AcDbPolyline") (90 . 2) (70 . 0)
(43 . 0.0) (10 2200.2262443439 3731.146719457) (10 2236.0485294118 3710.407239819))
((0 . "LWPOLYLINE") (100 . "AcDbEntity") (8 . "PLANTS") (62 . 94) (370 . 13) (100 . "AcDbPolyline") (90 . 3) (70 . 0)
(43 . 0.0) (10 2200.2262443439 3731.146719457) (10 2213.4205882353 3739.3720588235) (10 2232.2772624434
3740.5727375566))
((0 . "LWPOLYLINE") (100 . "AcDbEntity") (8 . "PLANTS") (62 . 94) (370 . 13) (100 . "AcDbPolyline") (90 . 3) (70 . 0)
(43 . 0.0) (10 2232.2772624434 3849.925) (10 2223.6798642534 3883.8616515837) (10 2202.1118778281 3917.7983031674))
((0 . "LWPOLYLINE") (100 . "AcDbEntity") (8 . "PLANTS") (62 . 94) (370 . 13) (100 . "AcDbPolyline") (90 . 2) (70 . 0)
(43 . 0.0) (10 2236.0485294118 750.3761312217) (10 2202.1118778281 757.9185520362))
((0 . "LWPOLYLINE") (100 . "AcDbEntity") (8 . "PLANTS") (62 . 94) (370 . 13) (100 . "AcDbPolyline") (90 . 3) (70 . 0)
(43 . 0.0) (10 2202.1118778281 757.9185520362) (10 2198.4889140271 784.3127828054) (10 2213.4240950226 833.3342760181))
((0 . "LWPOLYLINE") (100 . "AcDbEntity") (8 . "PLANTS") (62 . 94) (370 . 13) (100 . "AcDbPolyline") (90 . 2) (70 . 0)
(43 . 0.0) (10 2228.5067873303 584.4654977376) (10 2202.1118778281 576.9230769231))
((0 . "LWPOLYLINE") (100 . "AcDbEntity") (8 . "PLANTS") (62 . 94) (370 . 13) (100 . "AcDbPolyline") (90 . 2) (70 . 0)
(43 . 0.0) (10 2213.4240950226 4095.0226244344) (10 2205.8823529412 4125.1881221719))
((0 . "LWPOLYLINE") (100 . "AcDbEntity") (8 . "PLANTS") (62 . 94) (370 . 13) (100 . "AcDbPolyline") (90 . 2) (70 . 0)
(43 . 0.0) (10 2207.7679864253 1016.2132352941) (10 2243.589479638 1014.3297511312))
((0 . "LWPOLYLINE") (100 . "AcDbEntity") (8 . "PLANTS") (62 . 94) (370 . 13) (100 . "AcDbPolyline") (90 . 3) (70 . 0)
(43 . 0.0) (10 2207.7679864253 1016.2132352941) (10 2205.8889140271 991.7053167421) (10 2209.6528280543 961.5384615385))
((0 . "LWPOLYLINE") (100 . "AcDbEntity") (8 . "PLANTS") (62 . 94) (370 . 13) (100 . "AcDbPolyline") (90 . 2) (70 . 0)
(43 . 0.0) (10 2207.7679864253 1016.2132352941) (10 2213.4240950226 1070.8908371041))
((0 . "LWPOLYLINE") (100 . "AcDbEntity") (8 . "PLANTS") (62 . 94) (370 . 13) (100 . "AcDbPolyline") (90 . 2) (70 . 0)
(43 . 0.0) (10 2217.1945701357 3480.3924208145) (10 2209.6528280543 3476.6211538462))
((0 . "LWPOLYLINE") (100 . "AcDbEntity") (8 . "PLANTS") (62 . 94) (370 . 13) (100 . "AcDbPolyline") (90 . 3) (70 . 0)
(43 . 0.0) (10 2209.6528280543 1257.5424208145) (10 2213.1278280543 1266.900678733) (10 2209.6528280543 1308.44739819))
((0 . "LWPOLYLINE") (100 . "AcDbEntity") (8 . "PLANTS") (62 . 94) (370 . 13) (100 . "AcDbPolyline") (90 . 2) (70 . 0)
(43 . 0.0) (10 2209.6528280543 1257.5424208145) (10 2247.3607466063 1255.6561085973))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2209.6528280543 1257.5424208145 0.0) (10 2173.9360839379 1212.861883653 0.0) (10 2227.9278066313
1188.7204518949 0.0) (10 2220.9650452489 1150.0763574661 0.0))
((0 . "LWPOLYLINE") (100 . "AcDbEntity") (8 . "PLANTS") (62 . 94) (370 . 13) (100 . "AcDbPolyline") (90 . 3) (70 . 0)
(43 . 0.0) (10 2209.6528280543 961.5384615385) (10 2239.8124434389 961.3907239819) (10 2247.3607466063 957.7686651584))
((0 . "LWPOLYLINE") (100 . "AcDbEntity") (8 . "PLANTS") (62 . 94) (370 . 13) (100 . "AcDbPolyline") (90 . 2) (70 . 0)
(43 . 0.0) (10 2224.7363122172 878.5831447964) (10 2209.6528280543 878.5831447964))
((0 . "LWPOLYLINE") (100 . "AcDbEntity") (8 . "PLANTS") (62 . 94) (370 . 13) (100 . "AcDbPolyline") (90 . 2) (70 . 0)
(43 . 0.0) (10 2209.6528280543 878.5831447964) (10 2213.4240950226 833.3342760181))
((0 . "LWPOLYLINE") (100 . "AcDbEntity") (8 . "PLANTS") (62 . 94) (370 . 13) (100 . "AcDbPolyline") (90 . 2) (70 . 0)
(43 . 0.0) (10 2213.4240950226 4095.0226244344) (10 2254.9019230769 4091.2514705882))
((0 . "LWPOLYLINE") (100 . "AcDbEntity") (8 . "PLANTS") (62 . 94) (370 . 13) (100 . "AcDbPolyline") (90 . 3) (70 . 0)
(43 . 0.0) (10 2217.1945701357 4023.3781674208) (10 2213.5719457014 4030.9266968326) (10 2213.4240950226
4095.0226244344))
((0 . "LWPOLYLINE") (100 . "AcDbEntity") (8 . "PLANTS") (62 . 94) (370 . 13) (100 . "AcDbPolyline") (90 . 3) (70 . 0)
(43 . 0.0) (10 2213.4240950226 3542.6096153846) (10 2220.8171945701 3518.0995475113) (10 2217.1945701357
3480.3924208145))
((0 . "LWPOLYLINE") (100 . "AcDbEntity") (8 . "PLANTS") (62 . 94) (370 . 13) (100 . "AcDbPolyline") (90 . 3) (70 . 0)
(43 . 0.0) (10 2251.1312217195 3548.2657239819) (10 2228.5067873303 3548.1171945701) (10 2213.4240950226
3542.6096153846))
((0 . "LWPOLYLINE") (100 . "AcDbEntity") (8 . "PLANTS") (62 . 94) (370 . 13) (100 . "AcDbPolyline") (90 . 2) (70 . 0)
(43 . 0.0) (10 2232.2772624434 3435.1435520362) (10 2213.4240950226 3431.3722850679))
((0 . "LWPOLYLINE") (100 . "AcDbEntity") (8 . "PLANTS") (62 . 94) (370 . 13) (100 . "AcDbPolyline") (90 . 3) (70 . 0)
(43 . 0.0) (10 2213.4240950226 1070.8908371041) (10 2228.5067873303 1081.1459276018) (10 2239.8190045249
1082.2030542986))
((0 . "LWPOLYLINE") (100 . "AcDbEntity") (8 . "PLANTS") (62 . 94) (370 . 13) (100 . "AcDbPolyline") (90 . 2) (70 . 0)
(43 . 0.0) (10 2239.8190045249 833.3342760181) (10 2213.4240950226 833.3342760181))
((0 . "LWPOLYLINE") (100 . "AcDbEntity") (8 . "PLANTS") (62 . 94) (370 . 13) (100 . "AcDbPolyline") (90 . 2) (70 . 0)
(43 . 0.0) (10 2217.1945701357 4023.3781674208) (10 2217.1945701357 4015.8371040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2217.1945701357 4023.3781674208 0.0) (10 2255.4118442414 4013.334814118 0.0) (10 2263.7830373709
4066.8590111091 0.0) (10 2254.9019230769 4091.2514705882 0.0))
((0 . "LWPOLYLINE") (100 . "AcDbEntity") (8 . "PLANTS") (62 . 94) (370 . 13) (100 . "AcDbPolyline") (90 . 2) (70 . 0)
(43 . 0.0) (10 2224.7363122172 3989.4415158371) (10 2217.1945701357 4015.8371040724))
((0 . "LWPOLYLINE") (100 . "AcDbEntity") (8 . "PLANTS") (62 . 94) (370 . 13) (100 . "AcDbPolyline") (90 . 3) (70 . 0)
(43 . 0.0) (10 2232.2772624434 3476.6211538462) (10 2220.9650452489 3476.6211538462) (10 2217.1945701357
3480.3924208145))
((0 . "LWPOLYLINE") (100 . "AcDbEntity") (8 . "PLANTS") (62 . 94) (370 . 13) (100 . "AcDbPolyline") (90 . 2) (70 . 0)
(43 . 0.0) (10 2224.7363122172 380.8455882353) (10 2217.1945701357 377.0729638009))
((0 . "LWPOLYLINE") (100 . "AcDbEntity") (8 . "PLANTS") (62 . 94) (370 . 13) (100 . "AcDbPolyline") (90 . 3) (70 . 0)
(43 . 0.0) (10 2220.9650452489 3834.8416289593) (10 2224.7363122172 3842.3826923077) (10 2230.3924208145
3842.3826923077))
((0 . "LWPOLYLINE") (100 . "AcDbEntity") (8 . "PLANTS") (62 . 94) (370 . 13) (100 . "AcDbPolyline") (90 . 2) (70 . 0)
(43 . 0.0) (10 2220.9650452489 3834.8416289593) (10 2230.3924208145 3842.3826923077))
((0 . "LWPOLYLINE") (100 . "AcDbEntity") (8 . "PLANTS") (62 . 94) (370 . 13) (100 . "AcDbPolyline") (90 . 3) (70 . 0)
(43 . 0.0) (10 2220.9650452489 1150.0763574661) (10 2254.9016968326 1138.911199095) (10 2273.7556561086
1140.6476244344))
((0 . "LWPOLYLINE") (100 . "AcDbEntity") (8 . "PLANTS") (62 . 94) (370 . 13) (100 . "AcDbPolyline") (90 . 2) (70 . 0)
(43 . 0.0) (10 2228.5067873303 505.2790723982) (10 2220.9650452489 505.2790723982))
((0 . "LWPOLYLINE") (100 . "AcDbEntity") (8 . "PLANTS") (62 . 94) (370 . 13) (100 . "AcDbPolyline") (90 . 3) (70 . 0)
(43 . 0.0) (10 2243.589479638 569.3806561086) (10 2222.0214932127 527.9044117647) (10 2220.9650452489 505.2790723982))
((0 . "LWPOLYLINE") (100 . "AcDbEntity") (8 . "PLANTS") (62 . 94) (370 . 13) (100 . "AcDbPolyline") (90 . 2) (70 . 0)
(43 . 0.0) (10 2224.7363122172 328.0542986425) (10 2220.9650452489 320.5118778281))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2224.7363122172 878.5831447964 0.0) (10 2246.6675368777 876.2403137386 0.0) (10 2246.4816923615
848.3129838058 0.0) (10 2239.8190045249 833.3342760181 0.0))
((0 . "LWPOLYLINE") (100 . "AcDbEntity") (8 . "PLANTS") (62 . 94) (370 . 13) (100 . "AcDbPolyline") (90 . 2) (70 . 0)
(43 . 0.0) (10 2228.5067873303 923.8320135747) (10 2224.7363122172 878.5831447964))
((0 . "LWPOLYLINE") (100 . "AcDbEntity") (8 . "PLANTS") (62 . 94) (370 . 13) (100 . "AcDbPolyline") (90 . 2) (70 . 0)
(43 . 0.0) (10 2224.7363122172 475.1131221719) (10 2232.2772624434 452.4886877828))
((0 . "LWPOLYLINE") (100 . "AcDbEntity") (8 . "PLANTS") (62 . 94) (370 . 13) (100 . "AcDbPolyline") (90 . 2) (70 . 0)
(43 . 0.0) (10 2224.7363122172 475.1131221719) (10 2228.5067873303 505.2790723982))
((0 . "LWPOLYLINE") (100 . "AcDbEntity") (8 . "PLANTS") (62 . 94) (370 . 13) (100 . "AcDbPolyline") (90 . 2) (70 . 0)
(43 . 0.0) (10 2224.7363122172 380.8455882353) (10 2224.7363122172 411.0096153846))
((0 . "LWPOLYLINE") (100 . "AcDbEntity") (8 . "PLANTS") (62 . 94) (370 . 13) (100 . "AcDbPolyline") (90 . 2) (70 . 0)
(43 . 0.0) (10 2224.7363122172 380.8455882353) (10 2236.0485294118 380.8455882353))
((0 . "LWPOLYLINE") (100 . "AcDbEntity") (8 . "PLANTS") (62 . 94) (370 . 13) (100 . "AcDbPolyline") (90 . 2) (70 . 0)
(43 . 0.0) (10 2228.5067873303 923.8320135747) (10 2247.3607466063 938.9140271493))
((0 . "LWPOLYLINE") (100 . "AcDbEntity") (8 . "PLANTS") (62 . 94) (370 . 13) (100 . "AcDbPolyline") (90 . 2) (70 . 0)
(43 . 0.0) (10 2228.5067873303 584.4654977376) (10 2243.589479638 569.3806561086))
((0 . "LWPOLYLINE") (100 . "AcDbEntity") (8 . "PLANTS") (62 . 94) (370 . 13) (100 . "AcDbPolyline") (90 . 3) (70 . 0)
(43 . 0.0) (10 2239.8190045249 599.5475113122) (10 2233.3271493213 595.62239819) (10 2228.5067873303 584.4654977376))
((0 . "LWPOLYLINE") (100 . "AcDbEntity") (8 . "PLANTS") (62 . 94) (370 . 13) (100 . "AcDbPolyline") (90 . 2) (70 . 0)
(43 . 0.0) (10 2269.9851809955 505.2790723982) (10 2228.5067873303 505.2790723982))
((0 . "LWPOLYLINE") (100 . "AcDbEntity") (8 . "PLANTS") (62 . 94) (370 . 13) (100 . "AcDbPolyline") (90 . 3) (70 . 0)
(43 . 0.0) (10 2254.9016968326 3808.446040724) (10 2246.310520362 3827.3005656109) (10 2230.3924208145 3842.3826923077))
((0 . "LWPOLYLINE") (100 . "AcDbEntity") (8 . "PLANTS") (62 . 94) (370 . 13) (100 . "AcDbPolyline") (90 . 2) (70 . 0)
(43 . 0.0) (10 2232.2772624434 3849.925) (10 2230.3924208145 3842.3826923077))
((0 . "LWPOLYLINE") (100 . "AcDbEntity") (8 . "PLANTS") (62 . 94) (370 . 13) (100 . "AcDbPolyline") (90 . 2) (70 . 0)
(43 . 0.0) (10 2232.2772624434 3849.925) (10 2254.9016968326 3861.2372171946))
((0 . "LWPOLYLINE") (100 . "AcDbEntity") (8 . "PLANTS") (62 . 94) (370 . 13) (100 . "AcDbPolyline") (90 . 2) (70 . 0)
(43 . 0.0) (10 2232.2772624434 3740.5727375566) (10 2232.2772624434 3751.8849547511))
((0 . "LWPOLYLINE") (100 . "AcDbEntity") (8 . "PLANTS") (62 . 94) (370 . 13) (100 . "AcDbPolyline") (90 . 3) (70 . 0)
(43 . 0.0) (10 2232.2772624434 3751.8849547511) (10 2251.1312217195 3755.6429864253) (10 2266.2139140271
3751.8849547511))
((0 . "LWPOLYLINE") (100 . "AcDbEntity") (8 . "PLANTS") (62 . 94) (370 . 13) (100 . "AcDbPolyline") (90 . 3) (70 . 0)
(43 . 0.0) (10 2232.2772624434 3740.5727375566) (10 2235.9002262443 3733.0254524887) (10 2236.0485294118
3710.407239819))
((0 . "LWPOLYLINE") (100 . "AcDbEntity") (8 . "PLANTS") (62 . 94) (370 . 13) (100 . "AcDbPolyline") (90 . 2) (70 . 0)
(43 . 0.0) (10 2243.589479638 3582.2023755656) (10 2232.2772624434 3634.9928733032))
((0 . "LWPOLYLINE") (100 . "AcDbEntity") (8 . "PLANTS") (62 . 94) (370 . 13) (100 . "AcDbPolyline") (90 . 2) (70 . 0)
(43 . 0.0) (10 2258.6729638009 3642.5339366516) (10 2232.2772624434 3634.9928733032))
((0 . "LWPOLYLINE") (100 . "AcDbEntity") (8 . "PLANTS") (62 . 94) (370 . 13) (100 . "AcDbPolyline") (90 . 2) (70 . 0)
(43 . 0.0) (10 2232.2772624434 3435.1435520362) (10 2232.2772624434 3476.6211538462))
((0 . "LWPOLYLINE") (100 . "AcDbEntity") (8 . "PLANTS") (62 . 94) (370 . 13) (100 . "AcDbPolyline") (90 . 2) (70 . 0)
(43 . 0.0) (10 2232.2772624434 3476.6211538462) (10 2251.1312217195 3480.3924208145))
((0 . "LWPOLYLINE") (100 . "AcDbEntity") (8 . "PLANTS") (62 . 94) (370 . 13) (100 . "AcDbPolyline") (90 . 2) (70 . 0)
(43 . 0.0) (10 2232.2772624434 3435.1435520362) (10 2232.2772624434 3416.2895927602))
((0 . "LWPOLYLINE") (100 . "AcDbEntity") (8 . "PLANTS") (62 . 94) (370 . 13) (100 . "AcDbPolyline") (90 . 2) (70 . 0)
(43 . 0.0) (10 2232.2772624434 629.7143665158) (10 2239.8190045249 629.7143665158))
((0 . "LWPOLYLINE") (100 . "AcDbEntity") (8 . "PLANTS") (62 . 94) (370 . 13) (100 . "AcDbPolyline") (90 . 3) (70 . 0)
(43 . 0.0) (10 2232.2772624434 629.7143665158) (10 2233.481561086 671.1906108597) (10 2247.3607466063 682.5028280543))
((0 . "LWPOLYLINE") (100 . "AcDbEntity") (8 . "PLANTS") (62 . 94) (370 . 13) (100 . "AcDbPolyline") (90 . 3) (70 . 0)
(43 . 0.0) (10 2254.9016968326 3680.2417420814) (10 2241.0167420814 3691.553959276) (10 2236.0485294118 3710.407239819))
((0 . "LWPOLYLINE") (100 . "AcDbEntity") (8 . "PLANTS") (62 . 94) (370 . 13) (100 . "AcDbPolyline") (90 . 3) (70 . 0)
(43 . 0.0) (10 2245.4751131222 695.7013574661) (10 2236.1963800905 712.6696832579) (10 2236.0485294118 750.3761312217))
((0 . "LWPOLYLINE") (100 . "AcDbEntity") (8 . "PLANTS") (62 . 94) (370 . 13) (100 . "AcDbPolyline") (90 . 2) (70 . 0)
(43 . 0.0) (10 2236.0485294118 750.3761312217) (10 2258.6729638009 761.6883484163))
((0 . "LWPOLYLINE") (100 . "AcDbEntity") (8 . "PLANTS") (62 . 94) (370 . 13) (100 . "AcDbPolyline") (90 . 2) (70 . 0)
(43 . 0.0) (10 2273.7556561086 1044.4937782805) (10 2239.8190045249 1082.2030542986))
((0 . "LWPOLYLINE") (100 . "AcDbEntity") (8 . "PLANTS") (62 . 94) (370 . 13) (100 . "AcDbPolyline") (90 . 2) (70 . 0)
(43 . 0.0) (10 2239.8190045249 1082.2030542986) (10 2262.443438914 1093.5152714932))
((0 . "LWPOLYLINE") (100 . "AcDbEntity") (8 . "PLANTS") (62 . 94) (370 . 13) (100 . "AcDbPolyline") (90 . 2) (70 . 0)
(43 . 0.0) (10 2243.589479638 829.5616515837) (10 2239.8190045249 833.3342760181))
((0 . "LWPOLYLINE") (100 . "AcDbEntity") (8 . "PLANTS") (62 . 94) (370 . 13) (100 . "AcDbPolyline") (90 . 3) (70 . 0)
(43 . 0.0) (10 2243.589479638 829.5616515837) (10 2239.8190045249 829.5616515837) (10 2239.8190045249 833.3342760181))
((0 . "LWPOLYLINE") (100 . "AcDbEntity") (8 . "PLANTS") (62 . 94) (370 . 13) (100 . "AcDbPolyline") (90 . 2) (70 . 0)
(43 . 0.0) (10 2239.8190045249 599.5475113122) (10 2239.8190045249 629.7143665158))
((0 . "LWPOLYLINE") (100 . "AcDbEntity") (8 . "PLANTS") (62 . 94) (370 . 13) (100 . "AcDbPolyline") (90 . 3) (70 . 0)
(43 . 0.0) (10 2266.2139140271 644.7963800905) (10 2258.6660633484 634.6890271493) (10 2239.8190045249 629.7143665158))
((0 . "LWPOLYLINE") (100 . "AcDbEntity") (8 . "PLANTS") (62 . 94) (370 . 13) (100 . "AcDbPolyline") (90 . 3) (70 . 0)
(43 . 0.0) (10 2239.8190045249 599.5475113122) (10 2253.69739819 591.8580316742) (10 2258.6729638009 569.3806561086))
((0 . "LWPOLYLINE") (100 . "AcDbEntity") (8 . "PLANTS") (62 . 94) (370 . 13) (100 . "AcDbPolyline") (90 . 2) (70 . 0)
(43 . 0.0) (10 2251.1312217195 965.3082579186) (10 2243.589479638 1014.3297511312))
((0 . "LWPOLYLINE") (100 . "AcDbEntity") (8 . "PLANTS") (62 . 94) (370 . 13) (100 . "AcDbPolyline") (90 . 2) (70 . 0)
(43 . 0.0) (10 2273.7556561086 1044.4937782805) (10 2243.589479638 1014.3297511312))
((0 . "LWPOLYLINE") (100 . "AcDbEntity") (8 . "PLANTS") (62 . 94) (370 . 13) (100 . "AcDbPolyline") (90 . 2) (70 . 0)
(43 . 0.0) (10 2285.0678733032 829.5616515837) (10 2243.589479638 829.5616515837))
((0 . "LWPOLYLINE") (100 . "AcDbEntity") (8 . "PLANTS") (62 . 94) (370 . 13) (100 . "AcDbPolyline") (90 . 2) (70 . 0)
(43 . 0.0) (10 2243.589479638 806.9372171946) (10 2243.589479638 829.5616515837))
((0 . "LWPOLYLINE") (100 . "AcDbEntity") (8 . "PLANTS") (62 . 94) (370 . 13) (100 . "AcDbPolyline") (90 . 2) (70 . 0)
(43 . 0.0) (10 2258.6729638009 569.3806561086) (10 2243.589479638 569.3806561086))
((0 . "LWPOLYLINE") (100 . "AcDbEntity") (8 . "PLANTS") (62 . 94) (370 . 13) (100 . "AcDbPolyline") (90 . 2) (70 . 0)
(43 . 0.0) (10 2245.4751131222 695.7013574661) (10 2247.3607466063 682.5028280543))
((0 . "LWPOLYLINE") (100 . "AcDbEntity") (8 . "PLANTS") (62 . 94) (370 . 13) (100 . "AcDbPolyline") (90 . 2) (70 . 0)
(43 . 0.0) (10 2245.4751131222 695.7013574661) (10 2269.9851809955 705.1272624434))
((0 . "LWPOLYLINE") (100 . "AcDbEntity") (8 . "PLANTS") (62 . 94) (370 . 13) (100 . "AcDbPolyline") (90 . 2) (70 . 0)
(43 . 0.0) (10 2247.3607466063 1255.6561085973) (10 2273.7556561086 1225.4892533937))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2247.3607466063 1255.6561085973 0.0) (10 2263.5709801316 1285.6758865469 0.0) (10 2245.8778719914
1320.1393282269 0.0) (10 2262.443438914 1349.9236425339 0.0))
((0 . "LWPOLYLINE") (100 . "AcDbEntity") (8 . "PLANTS") (62 . 94) (370 . 13) (100 . "AcDbPolyline") (90 . 2) (70 . 0)
(43 . 0.0) (10 2247.3607466063 938.9140271493) (10 2247.3607466063 957.7686651584))
((0 . "LWPOLYLINE") (100 . "AcDbEntity") (8 . "PLANTS") (62 . 94) (370 . 13) (100 . "AcDbPolyline") (90 . 2) (70 . 0)
(43 . 0.0) (10 2251.1312217195 965.3082579186) (10 2247.3607466063 957.7686651584))
((0 . "LWPOLYLINE") (100 . "AcDbEntity") (8 . "PLANTS") (62 . 94) (370 . 13) (100 . "AcDbPolyline") (90 . 3) (70 . 0)
(43 . 0.0) (10 2247.3607466063 938.9140271493) (10 2269.984841629 917.4944570136) (10 2277.5261312217 916.2895927602))
((0 . "LWPOLYLINE") (100 . "AcDbEntity") (8 . "PLANTS") (62 . 94) (370 . 13) (100 . "AcDbPolyline") (90 . 3) (70 . 0)
(43 . 0.0) (10 2266.2139140271 644.7963800905) (10 2261.2391402715 667.4208144796) (10 2247.3607466063 682.5028280543))
((0 . "LWPOLYLINE") (100 . "AcDbEntity") (8 . "PLANTS") (62 . 94) (370 . 13) (100 . "AcDbPolyline") (90 . 2) (70 . 0)
(43 . 0.0) (10 2254.9016968326 3861.2372171946) (10 2251.1312217195 3872.5494343891))
((0 . "LWPOLYLINE") (100 . "AcDbEntity") (8 . "PLANTS") (62 . 94) (370 . 13) (100 . "AcDbPolyline") (90 . 2) (70 . 0)
(43 . 0.0) (10 2251.1312217195 3548.2657239819) (10 2251.1312217195 3563.3484162896))
((0 . "LWPOLYLINE") (100 . "AcDbEntity") (8 . "PLANTS") (62 . 94) (370 . 13) (100 . "AcDbPolyline") (90 . 3) (70 . 0)
(43 . 0.0) (10 2251.1312217195 3548.2657239819) (10 2262.2885746606 3525.6412895928) (10 2258.6729638009
3514.3290723982))
((0 . "LWPOLYLINE") (100 . "AcDbEntity") (8 . "PLANTS") (62 . 94) (370 . 13) (100 . "AcDbPolyline") (90 . 2) (70 . 0)
(43 . 0.0) (10 2300.1505656109 957.7686651584) (10 2251.1312217195 965.3082579186))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6115012958) (40
. 1) (40 . 1) (40 . 1) (40 . 1) (10 2254.9016968325 3861.2372171946 0.0) (10 2282.6880641156 3847.6893804395 0.0) (10
2301.5505897209 3799.4870535639 0.0) (10 2299.1760202203 3750.2207409838 0.0) (10 2322.7749999999 3748.1150452488 0.0))
((0 . "LWPOLYLINE") (100 . "AcDbEntity") (8 . "PLANTS") (62 . 94) (370 . 13) (100 . "AcDbPolyline") (90 . 2) (70 . 0)
(43 . 0.0) (10 2258.6729638009 3642.5339366516) (10 2254.9016968326 3680.2417420814))
((0 . "LWPOLYLINE") (100 . "AcDbEntity") (8 . "PLANTS") (62 . 94) (370 . 13) (100 . "AcDbPolyline") (90 . 2) (70 . 0)
(43 . 0.0) (10 2254.9016968326 3680.2417420814) (10 2296.3800904977 3684.0116515837))
((0 . "LWPOLYLINE") (100 . "AcDbEntity") (8 . "PLANTS") (62 . 94) (370 . 13) (100 . "AcDbPolyline") (90 . 2) (70 . 0)
(43 . 0.0) (10 2254.9016968326 429.8642533937) (10 2255.9916048106 425.5055041836))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2254.9019230769 4174.2081447964 0.0) (10 2275.3173651399 4181.4164049092 0.0) (10 2298.954300801
4167.1588603929 0.0) (10 2300.1505656109 4144.0426470588 0.0))
((0 . "LWPOLYLINE") (100 . "AcDbEntity") (8 . "PLANTS") (62 . 94) (370 . 13) (100 . "AcDbPolyline") (90 . 3) (70 . 0)
(43 . 0.0) (10 2254.9019230769 4174.2081447964) (10 2254.9019230769 4162.8959276018) (10 2254.9019230769
4091.2514705882))
((0 . "LWPOLYLINE") (100 . "AcDbEntity") (8 . "PLANTS") (62 . 94) (370 . 13) (100 . "AcDbPolyline") (90 . 2) (70 . 0)
(43 . 0.0) (10 2281.29739819 3642.5339366516) (10 2258.6729638009 3642.5339366516))
((0 . "LWPOLYLINE") (100 . "AcDbEntity") (8 . "PLANTS") (62 . 94) (370 . 13) (100 . "AcDbPolyline") (90 . 2) (70 . 0)
(43 . 0.0) (10 2258.6729638009 780.5429864253) (10 2258.6729638009 761.6883484163))
((0 . "LWPOLYLINE") (100 . "AcDbEntity") (8 . "PLANTS") (62 . 94) (370 . 13) (100 . "AcDbPolyline") (90 . 2) (70 . 0)
(43 . 0.0) (10 2258.6729638009 761.6883484163) (10 2300.1505656109 757.9185520362))
((0 . "LWPOLYLINE") (100 . "AcDbEntity") (8 . "PLANTS") (62 . 94) (370 . 13) (100 . "AcDbPolyline") (90 . 2) (70 . 0)
(43 . 0.0) (10 2258.6729638009 569.3806561086) (10 2273.7556561086 565.6108597285))
((0 . "LWPOLYLINE") (100 . "AcDbEntity") (8 . "PLANTS") (62 . 94) (370 . 13) (100 . "AcDbPolyline") (90 . 2) (70 . 0)
(43 . 0.0) (10 2278.8096209007 1352.6527033802) (10 2262.443438914 1349.9236425339))
((0 . "LWPOLYLINE") (100 . "AcDbEntity") (8 . "PLANTS") (62 . 94) (370 . 13) (100 . "AcDbPolyline") (90 . 3) (70 . 0)
(43 . 0.0) (10 2281.29739819 1044.4937782805) (10 2284.0053167421 1059.5786199095) (10 2262.443438914 1093.5152714932))
((0 . "LWPOLYLINE") (100 . "AcDbEntity") (8 . "PLANTS") (62 . 94) (370 . 13) (100 . "AcDbPolyline") (90 . 3) (70 . 0)
(43 . 0.0) (10 2273.7556561086 1119.9095022624) (10 2267.270361991 1112.3622171946) (10 2262.443438914 1093.5152714932))
((0 . "LWPOLYLINE") (100 . "AcDbEntity") (8 . "PLANTS") (62 . 94) (370 . 13) (100 . "AcDbPolyline") (90 . 3) (70 . 0)
(43 . 0.0) (10 2285.0678733032 3898.9437782805) (10 2274.8116515837 3914.0271493213) (10 2266.2139140271
3947.963800905))
((0 . "LWPOLYLINE") (100 . "AcDbEntity") (8 . "PLANTS") (62 . 94) (370 . 13) (100 . "AcDbPolyline") (90 . 3) (70 . 0)
(43 . 0.0) (10 2275.6412895928 3957.3910633484) (10 2269.9851809955 3955.5048642534) (10 2266.2139140271
3947.963800905))
((0 . "LWPOLYLINE") (100 . "AcDbEntity") (8 . "PLANTS") (62 . 94) (370 . 13) (100 . "AcDbPolyline") (90 . 2) (70 . 0)
(43 . 0.0) (10 2277.5261312217 641.0265837104) (10 2266.2139140271 644.7963800905))
((0 . "LWPOLYLINE") (100 . "AcDbEntity") (8 . "PLANTS") (62 . 94) (370 . 13) (100 . "AcDbPolyline") (90 . 2) (70 . 0)
(43 . 0.0) (10 2269.9851809955 505.2790723982) (10 2266.2139140271 535.4440045249))
((0 . "LWPOLYLINE") (100 . "AcDbEntity") (8 . "PLANTS") (62 . 94) (370 . 13) (100 . "AcDbPolyline") (90 . 2) (70 . 0)
(43 . 0.0) (10 2269.9851809955 505.2790723982) (10 2277.8100166299 505.2790723982))
((0 . "LWPOLYLINE") (100 . "AcDbEntity") (8 . "PLANTS") (62 . 94) (370 . 13) (100 . "AcDbPolyline") (90 . 2) (70 . 0)
(43 . 0.0) (10 2273.7556561086 4000.7537330317) (10 2292.6096153846 3989.4415158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2275.6412895928 3957.3910633484 0.0) (10 2255.602941305 3965.9536421203 0.0) (10 2261.3287737056
3990.0654633303 0.0) (10 2273.7556561086 4000.7537330317 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2273.7556561086 4000.7537330317 0.0) (10 2296.3969328003 4029.387740518 0.0) (10 2295.0416135387
4068.6397427637 0.0) (10 2296.3800904977 4102.5636877828 0.0))
((0 . "LWPOLYLINE") (100 . "AcDbEntity") (8 . "PLANTS") (62 . 94) (370 . 13) (100 . "AcDbPolyline") (90 . 2) (70 . 0)
(43 . 0.0) (10 2273.7556561086 1176.4705882353) (10 2273.7556561086 1225.4892533937))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2296.3800904977 1274.5107466063 0.0) (10 2296.1873355303 1257.8122602957 0.0) (10 2293.1333459243
1232.2269091659 0.0) (10 2273.7556561086 1225.4892533937 0.0))
((0 . "LWPOLYLINE") (100 . "AcDbEntity") (8 . "PLANTS") (62 . 94) (370 . 13) (100 . "AcDbPolyline") (90 . 2) (70 . 0)
(43 . 0.0) (10 2273.7556561086 1140.6476244344) (10 2273.7556561086 1176.4705882353))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5334220434) (40
. 1) (40 . 1) (40 . 1) (40 . 1) (10 2273.7556561086 1176.4705882353 0.0) (10 2303.9045963582 1168.8015366264 0.0) (10
2305.9773233167 1212.7260476098 0.0) (10 2337.1713111609 1233.9912397137 0.0) (10 2358.5972850679 1229.261877828 0.0))
((0 . "LWPOLYLINE") (100 . "AcDbEntity") (8 . "PLANTS") (62 . 94) (370 . 13) (100 . "AcDbPolyline") (90 . 2) (70 . 0)
(43 . 0.0) (10 2273.7556561086 1140.6476244344) (10 2273.7556561086 1119.9095022624))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2349.1707013575 1142.5339366516 0.0) (10 2324.3419301993 1128.1167942135 0.0) (10 2299.9817226317
1164.0353358654 0.0) (10 2273.7556561086 1140.6476244344 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2366.1390271493 1061.4621040724 0.0) (10 2352.5304943068 1116.5740907176 0.0) (10 2300.9471064693
1091.9136315186 0.0) (10 2273.7556561086 1119.9095022624 0.0))
((0 . "LWPOLYLINE") (100 . "AcDbEntity") (8 . "PLANTS") (62 . 94) (370 . 13) (100 . "AcDbPolyline") (90 . 2) (70 . 0)
(43 . 0.0) (10 2281.29739819 1044.4937782805) (10 2273.7556561086 1044.4937782805))
((0 . "LWPOLYLINE") (100 . "AcDbEntity") (8 . "PLANTS") (62 . 94) (370 . 13) (100 . "AcDbPolyline") (90 . 3) (70 . 0)
(43 . 0.0) (10 2275.6412895928 3957.3910633484) (10 2307.6923076923 3956.5615384615) (10 2356.7116515837
3978.1292986425))
((0 . "LWPOLYLINE") (100 . "AcDbEntity") (8 . "PLANTS") (62 . 94) (370 . 13) (100 . "AcDbPolyline") (90 . 3) (70 . 0)
(43 . 0.0) (10 2275.6412895928 3957.3910633484) (10 2291.4053167421 3978.1292986425) (10 2292.6096153846
3989.4415158371))
((0 . "LWPOLYLINE") (100 . "AcDbEntity") (8 . "PLANTS") (62 . 94) (370 . 13) (100 . "AcDbPolyline") (90 . 2) (70 . 0)
(43 . 0.0) (10 2286.6868820018 3365.7894100568) (10 2277.5261312217 3363.4989819005))
((0 . "LWPOLYLINE") (100 . "AcDbEntity") (8 . "PLANTS") (62 . 94) (370 . 13) (100 . "AcDbPolyline") (90 . 3) (70 . 0)
(43 . 0.0) (10 2277.5261312217 916.2895927602) (10 2278.5825791855 897.4349547511) (10 2296.3800904977 855.9587104072))
((0 . "LWPOLYLINE") (100 . "AcDbEntity") (8 . "PLANTS") (62 . 94) (370 . 13) (100 . "AcDbPolyline") (90 . 2) (70 . 0)
(43 . 0.0) (10 2277.5261312217 916.2895927602) (10 2296.3800904977 920.0593891403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2320.890158371 967.1945701357 0.0) (10 2287.2220404568 982.9231531307 0.0) (10 2315.7087960458
1028.0843870914 0.0) (10 2281.29739819 1044.4937782805 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2405.7317873304 3898.9437782806 0.0) (10 2371.9290803088 3859.8803388533 0.0) (10 2324.8545779515
3907.8757583872 0.0) (10 2285.0678733032 3898.9437782806 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3076026711)
(40 . 0.5828223513) (40 . 1) (40 . 1) (40 . 1) (40 . 1) (10 2285.0678733031 3898.9437782805 0.0) (10 2286.1530327119
3875.8177063389 0.0) (10 2317.0953617949 3855.1097108237 0.0) (10 2362.3205177112 3808.773068338 0.0) (10
2407.2312732553 3791.8443225776 0.0) (10 2383.1073529412 3751.8849547511 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2296.3800904978 1274.5107466063 0.0) (10 2273.4452570089 1292.73451472 0.0) (10 2302.7506599564
1317.9518695339 0.0) (10 2297.3126234063 1337.6190138444 0.0))
((0 . "LWPOLYLINE") (100 . "AcDbEntity") (8 . "PLANTS") (62 . 94) (370 . 13) (100 . "AcDbPolyline") (90 . 3) (70 . 0)
(43 . 0.0) (10 2285.0678733032 829.5616515837) (10 2288.9932126697 818.2494343891) (10 2307.6923076923 803.1674208145))
((0 . "LWPOLYLINE") (100 . "AcDbEntity") (8 . "PLANTS") (62 . 94) (370 . 13) (100 . "AcDbPolyline") (90 . 2) (70 . 0)
(43 . 0.0) (10 2285.0678733032 829.5616515837) (10 2296.3800904977 855.9587104072))
((0 . "LWPOLYLINE") (100 . "AcDbEntity") (8 . "PLANTS") (62 . 94) (370 . 13) (100 . "AcDbPolyline") (90 . 2) (70 . 0)
(43 . 0.0) (10 2326.5462669683 4034.6903846154) (10 2292.6096153846 3989.4415158371))
((0 . "LWPOLYLINE") (100 . "AcDbEntity") (8 . "PLANTS") (62 . 94) (370 . 13) (100 . "AcDbPolyline") (90 . 3) (70 . 0)
(43 . 0.0) (10 2296.3800904977 1274.5107466063) (10 2303.9283936652 1275.7141402715) (10 2322.775 1293.3625565611))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2326.5462669683 852.1860859728 0.0) (10 2338.2292087217 877.4141803148 0.0) (10 2320.299466545
909.3219948206 0.0) (10 2296.3800904977 920.0593891403 0.0))
((0 . "LWPOLYLINE") (100 . "AcDbEntity") (8 . "PLANTS") (62 . 94) (370 . 13) (100 . "AcDbPolyline") (90 . 2) (70 . 0)
(43 . 0.0) (10 2300.1505656109 957.7686651584) (10 2296.3800904977 920.0593891403))
((0 . "LWPOLYLINE") (100 . "AcDbEntity") (8 . "PLANTS") (62 . 94) (370 . 13) (100 . "AcDbPolyline") (90 . 2) (70 . 0)
(43 . 0.0) (10 2296.3800904977 855.9587104072) (10 2326.5462669683 852.1860859729))
((0 . "LWPOLYLINE") (100 . "AcDbEntity") (8 . "PLANTS") (62 . 94) (370 . 13) (100 . "AcDbPolyline") (90 . 2) (70 . 0)
(43 . 0.0) (10 2320.890158371 967.1945701357) (10 2300.1505656109 957.7686651584))
((0 . "LWPOLYLINE") (100 . "AcDbEntity") (8 . "PLANTS") (62 . 94) (370 . 13) (100 . "AcDbPolyline") (90 . 3) (70 . 0)
(43 . 0.0) (10 2300.1505656109 757.9185520362) (10 2315.2340497738 747.6626696833) (10 2325.6530094762 747.1762084547))
((0 . "LWPOLYLINE") (100 . "AcDbEntity") (8 . "PLANTS") (62 . 94) (370 . 13) (100 . "AcDbPolyline") (90 . 2) (70 . 0)
(43 . 0.0) (10 2300.1505656109 757.9185520362) (10 2307.6923076923 803.1674208145))
((0 . "LWPOLYLINE") (100 . "AcDbEntity") (8 . "PLANTS") (62 . 94) (370 . 13) (100 . "AcDbPolyline") (90 . 2) (70 . 0)
(43 . 0.0) (10 2307.6923076923 4121.4182126697) (10 2348.2184981598 4124.3122892497))
((0 . "LWPOLYLINE") (100 . "AcDbEntity") (8 . "PLANTS") (62 . 94) (370 . 13) (100 . "AcDbPolyline") (90 . 3) (70 . 0)
(43 . 0.0) (10 2330.3167420814 840.8738687783) (10 2317.9485294118 810.7147058824) (10 2307.6923076923 803.1674208145))
((0 . "LWPOLYLINE") (100 . "AcDbEntity") (8 . "PLANTS") (62 . 94) (370 . 13) (100 . "AcDbPolyline") (90 . 3) (70 . 0)
(43 . 0.0) (10 2319.0045248869 4072.3981900452) (10 2326.6941176471 4082.5127828054) (10 2360.482918552 4087.481561086))
((0 . "LWPOLYLINE") (100 . "AcDbEntity") (8 . "PLANTS") (62 . 94) (370 . 13) (100 . "AcDbPolyline") (90 . 2) (70 . 0)
(43 . 0.0) (10 2322.775 1293.3625565611) (10 2319.0045248869 1304.6747737557))
((0 . "LWPOLYLINE") (100 . "AcDbEntity") (8 . "PLANTS") (62 . 94) (370 . 13) (100 . "AcDbPolyline") (90 . 2) (70 . 0)
(43 . 0.0) (10 2320.890158371 967.1945701357) (10 2334.0872171946 957.7686651584))
((0 . "LWPOLYLINE") (100 . "AcDbEntity") (8 . "PLANTS") (62 . 94) (370 . 13) (100 . "AcDbPolyline") (90 . 3) (70 . 0)
(43 . 0.0) (10 2320.890158371 967.1945701357) (10 2336.6538461538 984.1628959276) (10 2341.628959276 1003.0175339367))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2330.3225586799 3627.3981271068 0.0) (10 2327.1205231381 3668.0499908174 0.0) (10 2344.9504801227
3709.2192087365 0.0) (10 2322.775 3748.1150452489 0.0))
((0 . "LWPOLYLINE") (100 . "AcDbEntity") (8 . "PLANTS") (62 . 94) (370 . 13) (100 . "AcDbPolyline") (90 . 3) (70 . 0)
(43 . 0.0) (10 2383.1073529412 3751.8849547511) (10 2334.0875565611 3751.7371040724) (10 2322.775 3748.1150452489))
((0 . "LWPOLYLINE") (100 . "AcDbEntity") (8 . "PLANTS") (62 . 94) (370 . 13) (100 . "AcDbPolyline") (90 . 2) (70 . 0)
(43 . 0.0) (10 2351.7821092934 1293.3625565611) (10 2322.775 1293.3625565611))
((0 . "LWPOLYLINE") (100 . "AcDbEntity") (8 . "PLANTS") (62 . 94) (370 . 13) (100 . "AcDbPolyline") (90 . 2) (70 . 0)
(43 . 0.0) (10 2330.3167420814 840.8738687783) (10 2326.5462669683 852.1860859729))
((0 . "LWPOLYLINE") (100 . "AcDbEntity") (8 . "PLANTS") (62 . 94) (370 . 13) (100 . "AcDbPolyline") (90 . 2) (70 . 0)
(43 . 0.0) (10 2330.3167420814 840.8738687783) (10 2334.0399329178 840.8738687783))
((0 . "LWPOLYLINE") (100 . "AcDbEntity") (8 . "PLANTS") (62 . 94) (370 . 13) (100 . "AcDbPolyline") (90 . 3) (70 . 0)
(43 . 0.0) (10 2386.8778280543 3936.6515837104) (10 2364.2533936652 3932.8804298643) (10 2334.0872171946
3936.6515837104))
((0 . "LWPOLYLINE") (100 . "AcDbEntity") (8 . "PLANTS") (62 . 94) (370 . 13) (100 . "AcDbPolyline") (90 . 3) (70 . 0)
(43 . 0.0) (10 2379.3360859729 938.9140271493) (10 2345.3997737557 956.7115384615) (10 2334.0872171946 957.7686651584))
((0 . "LWPOLYLINE") (100 . "AcDbEntity") (8 . "PLANTS") (62 . 94) (370 . 13) (100 . "AcDbPolyline") (90 . 3) (70 . 0)
(43 . 0.0) (10 2340.5485938714 913.58781537) (10 2338.914479638 916.2895927602) (10 2334.0872171946 957.7686651584))
((0 . "LWPOLYLINE") (100 . "AcDbEntity") (8 . "PLANTS") (62 . 94) (370 . 13) (100 . "AcDbPolyline") (90 . 2) (70 . 0)
(43 . 0.0) (10 2341.628959276 4038.4615384615) (10 2352.9411764706 4042.2326923077))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2341.628959276 1003.0175339367 0.0) (10 2373.0333554627 1002.4229617144 0.0) (10 2389.187760234
966.271324465 0.0) (10 2386.8778280543 938.9140271493 0.0))
((0 . "LWPOLYLINE") (100 . "AcDbEntity") (8 . "PLANTS") (62 . 94) (370 . 13) (100 . "AcDbPolyline") (90 . 3) (70 . 0)
(43 . 0.0) (10 2341.628959276 1003.0175339367) (10 2346.4562217195 1033.181561086) (10 2366.1390271493 1061.4621040724))
((0 . "LWPOLYLINE") (100 . "AcDbEntity") (8 . "PLANTS") (62 . 94) (370 . 13) (100 . "AcDbPolyline") (90 . 3) (70 . 0)
(43 . 0.0) (10 2349.1707013575 1142.5339366516) (10 2364.2533936652 1135.1399321267) (10 2420.814479638 1131.221719457))
((0 . "LWPOLYLINE") (100 . "AcDbEntity") (8 . "PLANTS") (62 . 94) (370 . 13) (100 . "AcDbPolyline") (90 . 3) (70 . 0)
(43 . 0.0) (10 2349.1707013575 1142.5339366516) (10 2360.3346153846 1214.1770361991) (10 2358.5972850679
1229.2618778281))
((0 . "LWPOLYLINE") (100 . "AcDbEntity") (8 . "PLANTS") (62 . 94) (370 . 13) (100 . "AcDbPolyline") (90 . 3) (70 . 0)
(43 . 0.0) (10 2364.2533936652 4008.296040724) (10 2357.9093891403 4015.8433257919) (10 2352.9411764706
4042.2326923077))
((0 . "LWPOLYLINE") (100 . "AcDbEntity") (8 . "PLANTS") (62 . 94) (370 . 13) (100 . "AcDbPolyline") (90 . 2) (70 . 0)
(43 . 0.0) (10 2360.482918552 4068.6270361991) (10 2352.9411764706 4042.2326923077))
((0 . "LWPOLYLINE") (100 . "AcDbEntity") (8 . "PLANTS") (62 . 94) (370 . 13) (100 . "AcDbPolyline") (90 . 3) (70 . 0)
(43 . 0.0) (10 2356.7116515837 3978.1292986425) (10 2364.4016968326 3968.0218325792) (10 2383.1073529412
3966.817081448))
((0 . "LWPOLYLINE") (100 . "AcDbEntity") (8 . "PLANTS") (62 . 94) (370 . 13) (100 . "AcDbPolyline") (90 . 2) (70 . 0)
(43 . 0.0) (10 2364.2533936652 4008.296040724) (10 2356.7116515837 3978.1292986425))
((0 . "LWPOLYLINE") (100 . "AcDbEntity") (8 . "PLANTS") (62 . 94) (370 . 13) (100 . "AcDbPolyline") (90 . 3) (70 . 0)
(43 . 0.0) (10 2359.2682462285 1287.2800703014) (10 2356.7182126697 1274.5107466063) (10 2358.5972850679
1229.2618778281))
((0 . "LWPOLYLINE") (100 . "AcDbEntity") (8 . "PLANTS") (62 . 94) (370 . 13) (100 . "AcDbPolyline") (90 . 3) (70 . 0)
(43 . 0.0) (10 2358.5972850679 1229.2618778281) (10 2401.960520362 1241.7712669683) (10 2415.1445907907
1260.5002644664))
((0 . "LWPOLYLINE") (100 . "AcDbEntity") (8 . "PLANTS") (62 . 94) (370 . 13) (100 . "AcDbPolyline") (90 . 2) (70 . 0)
(43 . 0.0) (10 2360.482918552 4087.481561086) (10 2360.482918552 4114.347447681))
((0 . "LWPOLYLINE") (100 . "AcDbEntity") (8 . "PLANTS") (62 . 94) (370 . 13) (100 . "AcDbPolyline") (90 . 2) (70 . 0)
(43 . 0.0) (10 2360.482918552 4068.6270361991) (10 2360.482918552 4087.481561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2360.482918552 4068.6270361991 0.0) (10 2374.1941947628 4067.0204401533 0.0) (10 2389.5338522779
4072.6683827506 0.0) (10 2397.1753041844 4084.5348843547 0.0))
((0 . "LWPOLYLINE") (100 . "AcDbEntity") (8 . "PLANTS") (62 . 94) (370 . 13) (100 . "AcDbPolyline") (90 . 2) (70 . 0)
(43 . 0.0) (10 2375.5656108597 3853.6949095023) (10 2360.482918552 3857.4660633484))
((0 . "LWPOLYLINE") (100 . "AcDbEntity") (8 . "PLANTS") (62 . 94) (370 . 13) (100 . "AcDbPolyline") (90 . 3) (70 . 0)
(43 . 0.0) (10 2413.2727375566 4027.149321267) (10 2401.960520362 4026.0926470588) (10 2364.2533936652 4008.296040724))
((0 . "LWPOLYLINE") (100 . "AcDbEntity") (8 . "PLANTS") (62 . 94) (370 . 13) (100 . "AcDbPolyline") (90 . 2) (70 . 0)
(43 . 0.0) (10 2522.6248717675 916.2895927602) (10 2522.6244343891 931.3716063348))
((0 . "LWPOLYLINE") (100 . "AcDbEntity") (8 . "PLANTS") (62 . 94) (370 . 13) (100 . "AcDbPolyline") (90 . 3) (70 . 0)
(43 . 0.0) (10 2366.1390271493 1061.4621040724) (10 2390.7966063348 1025.6419683258) (10 2432.1266968326
984.1628959276))
((0 . "LWPOLYLINE") (100 . "AcDbEntity") (8 . "PLANTS") (62 . 94) (370 . 13) (100 . "AcDbPolyline") (90 . 3) (70 . 0)
(43 . 0.0) (10 2401.960520362 1070.8908371041) (10 2386.8778280543 1069.8399321267) (10 2366.1390271493
1061.4621040724))
((0 . "LWPOLYLINE") (100 . "AcDbEntity") (8 . "PLANTS") (62 . 94) (370 . 13) (100 . "AcDbPolyline") (90 . 2) (70 . 0)
(43 . 0.0) (10 2379.3360859729 938.9140271493) (10 2377.0737443464 916.2895927602))
((0 . "LWPOLYLINE") (100 . "AcDbEntity") (8 . "PLANTS") (62 . 94) (370 . 13) (100 . "AcDbPolyline") (90 . 2) (70 . 0)
(43 . 0.0) (10 2379.3360859729 938.9140271493) (10 2386.8778280543 938.9140271493))
((0 . "LWPOLYLINE") (100 . "AcDbEntity") (8 . "PLANTS") (62 . 94) (370 . 13) (100 . "AcDbPolyline") (90 . 2) (70 . 0)
(43 . 0.0) (10 2386.8778280543 3936.6515837104) (10 2383.1073529412 3966.817081448))
((0 . "LWPOLYLINE") (100 . "AcDbEntity") (8 . "PLANTS") (62 . 94) (370 . 13) (100 . "AcDbPolyline") (90 . 2) (70 . 0)
(43 . 0.0) (10 2409.5022624434 3978.1292986425) (10 2383.1073529412 3966.817081448))
((0 . "LWPOLYLINE") (100 . "AcDbEntity") (8 . "PLANTS") (62 . 94) (370 . 13) (100 . "AcDbPolyline") (90 . 2) (70 . 0)
(43 . 0.0) (10 2383.1073529412 3751.8849547511) (10 2383.1070905116 3744.3438914027))
((0 . "LWPOLYLINE") (100 . "AcDbEntity") (8 . "PLANTS") (62 . 94) (370 . 13) (100 . "AcDbPolyline") (90 . 2) (70 . 0)
(43 . 0.0) (10 2386.8778280543 3936.6515837104) (10 2405.7317873303 3932.8804298643))
((0 . "LWPOLYLINE") (100 . "AcDbEntity") (8 . "PLANTS") (62 . 94) (370 . 13) (100 . "AcDbPolyline") (90 . 2) (70 . 0)
(43 . 0.0) (10 2413.2727375566 931.3716063348) (10 2386.8778280543 938.9140271493))
((0 . "LWPOLYLINE") (100 . "AcDbEntity") (8 . "PLANTS") (62 . 94) (370 . 13) (100 . "AcDbPolyline") (90 . 2) (70 . 0)
(43 . 0.0) (10 2409.5022624434 1199.0950226244) (10 2390.6483031674 1180.2403846154))
((0 . "LWPOLYLINE") (100 . "AcDbEntity") (8 . "PLANTS") (62 . 94) (370 . 13) (100 . "AcDbPolyline") (90 . 3) (70 . 0)
(43 . 0.0) (10 2401.960520362 3842.3826923077) (10 2420.814479638 3838.4578054299) (10 2450.9806561086 3804.6761312217))
((0 . "LWPOLYLINE") (100 . "AcDbEntity") (8 . "PLANTS") (62 . 94) (370 . 13) (100 . "AcDbPolyline") (90 . 3) (70 . 0)
(43 . 0.0) (10 2401.960520362 1070.8908371041) (10 2420.814479638 1053.0856334842) (10 2450.9806561086 1040.7239819005))
((0 . "LWPOLYLINE") (100 . "AcDbEntity") (8 . "PLANTS") (62 . 94) (370 . 13) (100 . "AcDbPolyline") (90 . 3) (70 . 0)
(43 . 0.0) (10 2401.960520362 1070.8908371041) (10 2404.8365384615 1089.7426470588) (10 2420.814479638 1108.5972850679))
((0 . "LWPOLYLINE") (100 . "AcDbEntity") (8 . "PLANTS") (62 . 94) (370 . 13) (100 . "AcDbPolyline") (90 . 2) (70 . 0)
(43 . 0.0) (10 2405.7317873303 3898.9437782805) (10 2405.7317873303 3932.8804298643))
((0 . "LWPOLYLINE") (100 . "AcDbEntity") (8 . "PLANTS") (62 . 94) (370 . 13) (100 . "AcDbPolyline") (90 . 2) (70 . 0)
(43 . 0.0) (10 2424.5849547511 3951.7349547511) (10 2405.7317873303 3932.8804298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2405.7317873303 3898.9437782805 0.0) (10 2436.0212613733 3889.6867743932 0.0) (10 2477.0061718157
3873.7564596298 0.0) (10 2507.5417420814 3891.4027149321 0.0))
((0 . "LWPOLYLINE") (100 . "AcDbEntity") (8 . "PLANTS") (62 . 94) (370 . 13) (100 . "AcDbPolyline") (90 . 3) (70 . 0)
(43 . 0.0) (10 2409.5022624434 3978.1292986425) (10 2419.7584841629 3966.817081448) (10 2424.5849547511
3951.7349547511))
((0 . "LWPOLYLINE") (100 . "AcDbEntity") (8 . "PLANTS") (62 . 94) (370 . 13) (100 . "AcDbPolyline") (90 . 2) (70 . 0)
(43 . 0.0) (10 2424.5849547511 4008.296040724) (10 2409.5022624434 3978.1292986425))
((0 . "LWPOLYLINE") (100 . "AcDbEntity") (8 . "PLANTS") (62 . 94) (370 . 13) (100 . "AcDbPolyline") (90 . 2) (70 . 0)
(43 . 0.0) (10 2477.3755656109 4096.9075791855) (10 2448.3010668736 4098.0278419897))
((0 . "LWPOLYLINE") (100 . "AcDbEntity") (8 . "PLANTS") (62 . 94) (370 . 13) (100 . "AcDbPolyline") (90 . 2) (70 . 0)
(43 . 0.0) (10 2413.2727375566 4027.149321267) (10 2424.5849547511 4008.296040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2413.2727375565 4027.149321267 0.0) (10 2421.5994818891 4059.5217554495 0.0) (10 2463.7773658734
4033.7264106088 0.0) (10 2447.2093891403 4008.296040724 0.0))
((0 . "LWPOLYLINE") (100 . "AcDbEntity") (8 . "PLANTS") (62 . 94) (370 . 13) (100 . "AcDbPolyline") (90 . 2) (70 . 0)
(43 . 0.0) (10 2435.8971719457 1259.4259049774) (10 2421.4809890068 1262.3106639567))
((0 . "LWPOLYLINE") (100 . "AcDbEntity") (8 . "PLANTS") (62 . 94) (370 . 13) (100 . "AcDbPolyline") (90 . 2) (70 . 0)
(43 . 0.0) (10 2420.814479638 1108.5972850679) (10 2420.814479638 1131.221719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2420.814479638 1131.221719457 0.0) (10 2427.9847595574 1175.727491886 0.0) (10 2474.3921356495
1211.7753423965 0.0) (10 2518.853959276 1199.0950226244 0.0))
((0 . "LWPOLYLINE") (100 . "AcDbEntity") (8 . "PLANTS") (62 . 94) (370 . 13) (100 . "AcDbPolyline") (90 . 2) (70 . 0)
(43 . 0.0) (10 2420.814479638 1108.5972850679) (10 2435.8971719457 1108.5972850679))
((0 . "LWPOLYLINE") (100 . "AcDbEntity") (8 . "PLANTS") (62 . 94) (370 . 13) (100 . "AcDbPolyline") (90 . 2) (70 . 0)
(43 . 0.0) (10 2424.5849547511 4008.296040724) (10 2447.2093891403 4008.296040724))
((0 . "LWPOLYLINE") (100 . "AcDbEntity") (8 . "PLANTS") (62 . 94) (370 . 13) (100 . "AcDbPolyline") (90 . 2) (70 . 0)
(43 . 0.0) (10 2424.5849547511 3951.7349547511) (10 2458.5216063348 3951.7349547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2435.8971719457 1108.5972850679 0.0) (10 2454.2640228438 1059.226041444 0.0) (10 2513.7244769674
1043.5391403363 0.0) (10 2556.5610859729 1063.3484162896 0.0))
((0 . "LWPOLYLINE") (100 . "AcDbEntity") (8 . "PLANTS") (62 . 94) (370 . 13) (100 . "AcDbPolyline") (90 . 3) (70 . 0)
(43 . 0.0) (10 2469.8338235294 1123.6792986425) (10 2450.9806561086 1122.4759049774) (10 2435.8971719457
1108.5972850679))
((0 . "LWPOLYLINE") (100 . "AcDbEntity") (8 . "PLANTS") (62 . 94) (370 . 13) (100 . "AcDbPolyline") (90 . 3) (70 . 0)
(43 . 0.0) (10 2473.6050904977 931.3716063348) (10 2458.5216063348 941.6281674208) (10 2439.668438914 942.6838235294))
((0 . "LWPOLYLINE") (100 . "AcDbEntity") (8 . "PLANTS") (62 . 94) (370 . 13) (100 . "AcDbPolyline") (90 . 2) (70 . 0)
(43 . 0.0) (10 2447.2093891403 4008.296040724) (10 2462.2928733032 4008.296040724))
((0 . "LWPOLYLINE") (100 . "AcDbEntity") (8 . "PLANTS") (62 . 94) (370 . 13) (100 . "AcDbPolyline") (90 . 3) (70 . 0)
(43 . 0.0) (10 2507.5417420814 3914.0271493213) (10 2477.3755656109 3929.2583710407) (10 2458.5216063348
3951.7349547511))
((0 . "LWPOLYLINE") (100 . "AcDbEntity") (8 . "PLANTS") (62 . 94) (370 . 13) (100 . "AcDbPolyline") (90 . 2) (70 . 0)
(43 . 0.0) (10 2458.5216063348 3951.7349547511) (10 2462.2928733032 4008.296040724))
((0 . "LWPOLYLINE") (100 . "AcDbEntity") (8 . "PLANTS") (62 . 94) (370 . 13) (100 . "AcDbPolyline") (90 . 3) (70 . 0)
(43 . 0.0) (10 2462.2928733032 4008.296040724) (10 2481.146040724 4009.4998868778) (10 2492.4582579186 4019.6082579186))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2469.8338235294 1229.2618778281 0.0) (10 2471.896812371 1242.8290397182 0.0) (10 2462.434722917
1277.6116588066 0.0) (10 2486.6810881788 1280.9392637201 0.0))
((0 . "LWPOLYLINE") (100 . "AcDbEntity") (8 . "PLANTS") (62 . 94) (370 . 13) (100 . "AcDbPolyline") (90 . 3) (70 . 0)
(43 . 0.0) (10 2469.8338235294 1123.6792986425) (10 2488.6877828054 1113.4179864253) (10 2503.7704751131
1112.367081448))
((0 . "LWPOLYLINE") (100 . "AcDbEntity") (8 . "PLANTS") (62 . 94) (370 . 13) (100 . "AcDbPolyline") (90 . 3) (70 . 0)
(43 . 0.0) (10 2469.8338235294 1123.6792986425) (10 2484.9169683258 1141.3290723982) (10 2496.2295248869
1142.5339366516))
((0 . "LWPOLYLINE") (100 . "AcDbEntity") (8 . "PLANTS") (62 . 94) (370 . 13) (100 . "AcDbPolyline") (90 . 2) (70 . 0)
(43 . 0.0) (10 2473.6050904977 931.3716063348) (10 2475.9232637675 916.2895927602))
((0 . "LWPOLYLINE") (100 . "AcDbEntity") (8 . "PLANTS") (62 . 94) (370 . 13) (100 . "AcDbPolyline") (90 . 3) (70 . 0)
(43 . 0.0) (10 2473.6050904977 931.3716063348) (10 2496.2295248869 935.1442307692) (10 2522.6244343891 931.3716063348))
((0 . "LWPOLYLINE") (100 . "AcDbEntity") (8 . "PLANTS") (62 . 94) (370 . 13) (100 . "AcDbPolyline") (90 . 2) (70 . 0)
(43 . 0.0) (10 2477.3755656109 4096.9075791855) (10 2496.2295248869 4095.0226244344))
((0 . "LWPOLYLINE") (100 . "AcDbEntity") (8 . "PLANTS") (62 . 94) (370 . 13) (100 . "AcDbPolyline") (90 . 3) (70 . 0)
(43 . 0.0) (10 2492.4582579186 4034.6903846154) (10 2481.3009049774 4049.7737556561) (10 2477.3755656109
4096.9075791855))
((0 . "LWPOLYLINE") (100 . "AcDbEntity") (8 . "PLANTS") (62 . 94) (370 . 13) (100 . "AcDbPolyline") (90 . 2) (70 . 0)
(43 . 0.0) (10 2477.3755656109 4096.9075791855) (10 2477.4163784832 4106.3465024496))
((0 . "LWPOLYLINE") (100 . "AcDbEntity") (8 . "PLANTS") (62 . 94) (370 . 13) (100 . "AcDbPolyline") (90 . 3) (70 . 0)
(43 . 0.0) (10 2503.7707013575 4113.8763089851) (10 2503.7707013575 4110.1059954751) (10 2496.2295248869
4095.0226244344))
((0 . "LWPOLYLINE") (100 . "AcDbEntity") (8 . "PLANTS") (62 . 94) (370 . 13) (100 . "AcDbPolyline") (90 . 2) (70 . 0)
(43 . 0.0) (10 2490.5698529412 1282.0503393665) (10 2507.5417420814 1282.0503393665))
((0 . "LWPOLYLINE") (100 . "AcDbEntity") (8 . "PLANTS") (62 . 94) (370 . 13) (100 . "AcDbPolyline") (90 . 2) (70 . 0)
(43 . 0.0) (10 2492.4582579186 4034.6903846154) (10 2492.4582579186 4019.6082579186))
((0 . "LWPOLYLINE") (100 . "AcDbEntity") (8 . "PLANTS") (62 . 94) (370 . 13) (100 . "AcDbPolyline") (90 . 3) (70 . 0)
(43 . 0.0) (10 2507.5417420814 4064.8571266968) (10 2504.6657239819 4049.7737556561) (10 2492.4582579186
4034.6903846154))
((0 . "LWPOLYLINE") (100 . "AcDbEntity") (8 . "PLANTS") (62 . 94) (370 . 13) (100 . "AcDbPolyline") (90 . 3) (70 . 0)
(43 . 0.0) (10 2507.5417420814 3970.5882352941) (10 2498.8023755656 4015.6824660633) (10 2492.4582579186
4019.6082579186))
((0 . "LWPOLYLINE") (100 . "AcDbEntity") (8 . "PLANTS") (62 . 94) (370 . 13) (100 . "AcDbPolyline") (90 . 3) (70 . 0)
(43 . 0.0) (10 2507.5417420814 4064.8571266968) (10 2506.3374434389 4083.7104072398) (10 2496.2295248869
4095.0226244344))
((0 . "LWPOLYLINE") (100 . "AcDbEntity") (8 . "PLANTS") (62 . 94) (370 . 13) (100 . "AcDbPolyline") (90 . 2) (70 . 0)
(43 . 0.0) (10 2511.3122171946 1119.9095022624) (10 2496.2295248869 1142.5339366516))
((0 . "LWPOLYLINE") (100 . "AcDbEntity") (8 . "PLANTS") (62 . 94) (370 . 13) (100 . "AcDbPolyline") (90 . 3) (70 . 0)
(43 . 0.0) (10 2496.2295248869 1142.5339366516) (10 2500.1548642534 1149.0261312217) (10 2518.853959276
1157.6159502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2662.1415158371 3797.1338235294 0.0) (10 2610.5020612269 3809.4417522748 0.0) (10 2555.8705946391
3805.4580707902 0.0) (10 2503.7704751131 3797.1338235294 0.0))
((0 . "LWPOLYLINE") (100 . "AcDbEntity") (8 . "PLANTS") (62 . 94) (370 . 13) (100 . "AcDbPolyline") (90 . 2) (70 . 0)
(43 . 0.0) (10 2507.5417420814 1104.8274886878) (10 2503.7704751131 1112.367081448))
((0 . "LWPOLYLINE") (100 . "AcDbEntity") (8 . "PLANTS") (62 . 94) (370 . 13) (100 . "AcDbPolyline") (90 . 2) (70 . 0)
(43 . 0.0) (10 2511.3122171946 1119.9095022624) (10 2503.7704751131 1112.367081448))
((0 . "LWPOLYLINE") (100 . "AcDbEntity") (8 . "PLANTS") (62 . 94) (370 . 13) (100 . "AcDbPolyline") (90 . 2) (70 . 0)
(43 . 0.0) (10 2533.9366515837 995.4751131222) (10 2503.7704751131 1018.0995475113))
((0 . "LWPOLYLINE") (100 . "AcDbEntity") (8 . "PLANTS") (62 . 94) (370 . 13) (100 . "AcDbPolyline") (90 . 2) (70 . 0)
(43 . 0.0) (10 2537.7073529412 4064.8571266968) (10 2507.5417420814 4064.8571266968))
((0 . "LWPOLYLINE") (100 . "AcDbEntity") (8 . "PLANTS") (62 . 94) (370 . 13) (100 . "AcDbPolyline") (90 . 2) (70 . 0)
(43 . 0.0) (10 2507.5417420814 3914.0271493213) (10 2507.5417420814 3891.4027149321))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2507.5417420815 3914.0271493213 0.0) (10 2516.5689958342 3933.9088848466 0.0) (10 2539.8372052076
3943.0287114677 0.0) (10 2560.331561086 3940.4227375566 0.0))
((0 . "LWPOLYLINE") (100 . "AcDbEntity") (8 . "PLANTS") (62 . 94) (370 . 13) (100 . "AcDbPolyline") (90 . 3) (70 . 0)
(43 . 0.0) (10 2560.331561086 3898.9437782805) (10 2541.4783936652 3891.5507918552) (10 2507.5417420814
3891.4027149321))
((0 . "LWPOLYLINE") (100 . "AcDbEntity") (8 . "PLANTS") (62 . 94) (370 . 13) (100 . "AcDbPolyline") (90 . 3) (70 . 0)
(43 . 0.0) (10 2507.5417420814 1282.0503393665) (10 2514.934841629 1248.1136877828) (10 2518.853959276 1199.0950226244))
((0 . "LWPOLYLINE") (100 . "AcDbEntity") (8 . "PLANTS") (62 . 94) (370 . 13) (100 . "AcDbPolyline") (90 . 2) (70 . 0)
(43 . 0.0) (10 2507.5417420814 1282.0503393665) (10 2517.9856863049 1289.8834346133))
((0 . "LWPOLYLINE") (100 . "AcDbEntity") (8 . "PLANTS") (62 . 94) (370 . 13) (100 . "AcDbPolyline") (90 . 2) (70 . 0)
(43 . 0.0) (10 2511.3122171946 1119.9095022624) (10 2526.3949095023 1119.9095022624))
((0 . "LWPOLYLINE") (100 . "AcDbEntity") (8 . "PLANTS") (62 . 94) (370 . 13) (100 . "AcDbPolyline") (90 . 3) (70 . 0)
(43 . 0.0) (10 2522.6244343891 1195.3252262443) (10 2522.6244343891 1199.0950226244) (10 2518.853959276
1199.0950226244))
((0 . "LWPOLYLINE") (100 . "AcDbEntity") (8 . "PLANTS") (62 . 94) (370 . 13) (100 . "AcDbPolyline") (90 . 2) (70 . 0)
(43 . 0.0) (10 2522.6244343891 1195.3252262443) (10 2518.853959276 1199.0950226244))
((0 . "LWPOLYLINE") (100 . "AcDbEntity") (8 . "PLANTS") (62 . 94) (370 . 13) (100 . "AcDbPolyline") (90 . 3) (70 . 0)
(43 . 0.0) (10 2526.3949095023 1119.9095022624) (10 2530.0176470588 1138.7641402715) (10 2518.853959276
1157.6159502262))
((0 . "LWPOLYLINE") (100 . "AcDbEntity") (8 . "PLANTS") (62 . 94) (370 . 13) (100 . "AcDbPolyline") (90 . 3) (70 . 0)
(43 . 0.0) (10 2522.6244343891 1195.3252262443) (10 2519.0018099548 1187.7759049774) (10 2518.853959276
1157.6159502262))
((0 . "LWPOLYLINE") (100 . "AcDbEntity") (8 . "PLANTS") (62 . 94) (370 . 13) (100 . "AcDbPolyline") (90 . 2) (70 . 0)
(43 . 0.0) (10 2522.6244343891 1195.3252262443) (10 2567.8733031674 1187.7828054299))
((0 . "LWPOLYLINE") (100 . "AcDbEntity") (8 . "PLANTS") (62 . 94) (370 . 13) (100 . "AcDbPolyline") (90 . 2) (70 . 0)
(43 . 0.0) (10 2522.6244343891 931.3716063348) (10 2541.4783936652 938.9140271493))
((0 . "LWPOLYLINE") (100 . "AcDbEntity") (8 . "PLANTS") (62 . 94) (370 . 13) (100 . "AcDbPolyline") (90 . 3) (70 . 0)
(43 . 0.0) (10 2526.3949095023 1119.9095022624) (10 2551.5863122172 1097.2788461538) (10 2556.5610859729
1063.3484162896))
((0 . "LWPOLYLINE") (100 . "AcDbEntity") (8 . "PLANTS") (62 . 94) (370 . 13) (100 . "AcDbPolyline") (90 . 3) (70 . 0)
(43 . 0.0) (10 2533.9366515837 995.4751131222) (10 2541.3300904977 961.5384615385) (10 2541.4783936652 938.9140271493))
((0 . "LWPOLYLINE") (100 . "AcDbEntity") (8 . "PLANTS") (62 . 94) (370 . 13) (100 . "AcDbPolyline") (90 . 3) (70 . 0)
(43 . 0.0) (10 2533.9366515837 995.4751131222) (10 2552.7906108597 1005.4416289593) (10 2575.4150452489 987.9326923077))
((0 . "LWPOLYLINE") (100 . "AcDbEntity") (8 . "PLANTS") (62 . 94) (370 . 13) (100 . "AcDbPolyline") (90 . 2) (70 . 0)
(43 . 0.0) (10 2537.7073529412 4123.5724951519) (10 2537.7073529412 4064.8571266968))
((0 . "LWPOLYLINE") (100 . "AcDbEntity") (8 . "PLANTS") (62 . 94) (370 . 13) (100 . "AcDbPolyline") (90 . 3) (70 . 0)
(43 . 0.0) (10 2537.7073529412 4064.8571266968) (10 2542.5343891403 4049.7737556561) (10 2564.1028280543
4027.149321267))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4737512738) (40
. 1) (40 . 1) (40 . 1) (40 . 1) (10 2541.4783936651 938.9140271492 0.0) (10 2574.8052342391 933.1471794655 0.0) (10
2646.9236446287 933.2194351234 0.0) (10 2718.7862693925 932.8002497784 0.0) (10 2756.410520362 935.1442307692 0.0))
((0 . "LWPOLYLINE") (100 . "AcDbEntity") (8 . "PLANTS") (62 . 94) (370 . 13) (100 . "AcDbPolyline") (90 . 2) (70 . 0)
(43 . 0.0) (10 2560.331561086 4008.296040724) (10 2545.2488687783 4000.7537330317))
((0 . "LWPOLYLINE") (100 . "AcDbEntity") (8 . "PLANTS") (62 . 94) (370 . 13) (100 . "AcDbPolyline") (90 . 3) (70 . 0)
(43 . 0.0) (10 2556.5610859729 1063.3484162896) (10 2601.8099547511 1063.4961538462) (10 2613.1221719457
1067.1182126697))
((0 . "LWPOLYLINE") (100 . "AcDbEntity") (8 . "PLANTS") (62 . 94) (370 . 13) (100 . "AcDbPolyline") (90 . 3) (70 . 0)
(43 . 0.0) (10 2560.331561086 4008.296040724) (10 2567.725 3989.4415158371) (10 2564.1028280543 3951.7349547511))
((0 . "LWPOLYLINE") (100 . "AcDbEntity") (8 . "PLANTS") (62 . 94) (370 . 13) (100 . "AcDbPolyline") (90 . 2) (70 . 0)
(43 . 0.0) (10 2560.331561086 4008.296040724) (10 2564.1028280543 4019.6082579186))
((0 . "LWPOLYLINE") (100 . "AcDbEntity") (8 . "PLANTS") (62 . 94) (370 . 13) (100 . "AcDbPolyline") (90 . 2) (70 . 0)
(43 . 0.0) (10 2560.331561086 3898.9437782805) (10 2560.331561086 3940.4227375566))
((0 . "LWPOLYLINE") (100 . "AcDbEntity") (8 . "PLANTS") (62 . 94) (370 . 13) (100 . "AcDbPolyline") (90 . 2) (70 . 0)
(43 . 0.0) (10 2564.1028280543 3951.7349547511) (10 2560.331561086 3940.4227375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2624.4343891403 3891.4027149321 0.0) (10 2603.8560075982 3883.1769128409 0.0) (10 2577.0823898699
3881.9376490614 0.0) (10 2560.331561086 3898.9437782805 0.0))
((0 . "LWPOLYLINE") (100 . "AcDbEntity") (8 . "PLANTS") (62 . 94) (370 . 13) (100 . "AcDbPolyline") (90 . 2) (70 . 0)
(43 . 0.0) (10 2564.1028280543 4019.6082579186) (10 2564.1028280543 4027.149321267))
((0 . "LWPOLYLINE") (100 . "AcDbEntity") (8 . "PLANTS") (62 . 94) (370 . 13) (100 . "AcDbPolyline") (90 . 3) (70 . 0)
(43 . 0.0) (10 2564.1028280543 4027.149321267) (10 2571.6440045249 4038.4615384615) (10 2571.6440045249
4133.2686813187))
((0 . "LWPOLYLINE") (100 . "AcDbEntity") (8 . "PLANTS") (62 . 94) (370 . 13) (100 . "AcDbPolyline") (90 . 2) (70 . 0)
(43 . 0.0) (10 2564.1028280543 4019.6082579186) (10 2605.5804298643 4038.4615384615))
((0 . "LWPOLYLINE") (100 . "AcDbEntity") (8 . "PLANTS") (62 . 94) (370 . 13) (100 . "AcDbPolyline") (90 . 2) (70 . 0)
(43 . 0.0) (10 2594.2682126697 3955.5048642534) (10 2564.1028280543 3951.7349547511))
((0 . "LWPOLYLINE") (100 . "AcDbEntity") (8 . "PLANTS") (62 . 94) (370 . 13) (100 . "AcDbPolyline") (90 . 2) (70 . 0)
(43 . 0.0) (10 2586.7272624434 1187.7828054299) (10 2567.8733031674 1187.7828054299))
((0 . "LWPOLYLINE") (100 . "AcDbEntity") (8 . "PLANTS") (62 . 94) (370 . 13) (100 . "AcDbPolyline") (90 . 2) (70 . 0)
(43 . 0.0) (10 2571.5418423156 1305.1851934735) (10 2567.8733031674 1187.7828054299))
((0 . "LWPOLYLINE") (100 . "AcDbEntity") (8 . "PLANTS") (62 . 94) (370 . 13) (100 . "AcDbPolyline") (90 . 3) (70 . 0)
(43 . 0.0) (10 2594.2682126697 1123.6792986425) (10 2575.5628959276 1128.6553167421) (10 2567.8733031674
1138.7641402715))
((0 . "LWPOLYLINE") (100 . "AcDbEntity") (8 . "PLANTS") (62 . 94) (370 . 13) (100 . "AcDbPolyline") (90 . 3) (70 . 0)
(43 . 0.0) (10 2586.7272624434 1187.7828054299) (10 2587.7832579186 1168.9281674208) (10 2601.8099547511
1138.7641402715))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2586.7272624435 1187.7828054298 0.0) (10 2619.6424602369 1193.1101787834 0.0) (10 2595.1521253072
1249.4756792008 0.0) (10 2624.4343891403 1263.1985294118 0.0))
((0 . "LWPOLYLINE") (100 . "AcDbEntity") (8 . "PLANTS") (62 . 94) (370 . 13) (100 . "AcDbPolyline") (90 . 2) (70 . 0)
(43 . 0.0) (10 2594.2682126697 3955.5048642534) (10 2624.4343891403 3906.4860859729))
((0 . "LWPOLYLINE") (100 . "AcDbEntity") (8 . "PLANTS") (62 . 94) (370 . 13) (100 . "AcDbPolyline") (90 . 2) (70 . 0)
(43 . 0.0) (10 2598.039479638 3963.0471719457) (10 2594.2682126697 3955.5048642534))
((0 . "LWPOLYLINE") (100 . "AcDbEntity") (8 . "PLANTS") (62 . 94) (370 . 13) (100 . "AcDbPolyline") (90 . 3) (70 . 0)
(43 . 0.0) (10 2594.2682126697 1123.6792986425) (10 2595.4725113122 1108.5972850679) (10 2609.3516968326
1097.2850678733))
((0 . "LWPOLYLINE") (100 . "AcDbEntity") (8 . "PLANTS") (62 . 94) (370 . 13) (100 . "AcDbPolyline") (90 . 2) (70 . 0)
(43 . 0.0) (10 2594.2682126697 1123.6792986425) (10 2601.8099547511 1138.7641402715))
((0 . "LWPOLYLINE") (100 . "AcDbEntity") (8 . "PLANTS") (62 . 94) (370 . 13) (100 . "AcDbPolyline") (90 . 3) (70 . 0)
(43 . 0.0) (10 2598.039479638 3963.0471719457) (10 2605.7352941176 3985.5231900452) (10 2624.4343891403
3993.2126696833))
((0 . "LWPOLYLINE") (100 . "AcDbEntity") (8 . "PLANTS") (62 . 94) (370 . 13) (100 . "AcDbPolyline") (90 . 3) (70 . 0)
(43 . 0.0) (10 2598.039479638 3963.0471719457) (10 2620.6570135747 3963.1950226244) (10 2628.2048642534 3966.817081448))
((0 . "LWPOLYLINE") (100 . "AcDbEntity") (8 . "PLANTS") (62 . 94) (370 . 13) (100 . "AcDbPolyline") (90 . 2) (70 . 0)
(43 . 0.0) (10 2601.8099547511 1138.7641402715) (10 2620.6639140271 1138.7641402715))
((0 . "LWPOLYLINE") (100 . "AcDbEntity") (8 . "PLANTS") (62 . 94) (370 . 13) (100 . "AcDbPolyline") (90 . 2) (70 . 0)
(43 . 0.0) (10 2613.1221719457 4038.4615384615) (10 2605.5804298643 4038.4615384615))
((0 . "LWPOLYLINE") (100 . "AcDbEntity") (8 . "PLANTS") (62 . 94) (370 . 13) (100 . "AcDbPolyline") (90 . 3) (70 . 0)
(43 . 0.0) (10 2605.5804298643 4038.4615384615) (10 2614.3133484163 4083.7104072398) (10 2628.2048642534
4102.5636877828))
((0 . "LWPOLYLINE") (100 . "AcDbEntity") (8 . "PLANTS") (62 . 94) (370 . 13) (100 . "AcDbPolyline") (90 . 2) (70 . 0)
(43 . 0.0) (10 2609.3516968326 1097.2850678733) (10 2613.1221719457 1067.1182126697))
((0 . "LWPOLYLINE") (100 . "AcDbEntity") (8 . "PLANTS") (62 . 94) (370 . 13) (100 . "AcDbPolyline") (90 . 3) (70 . 0)
(43 . 0.0) (10 2609.3516968326 1097.2850678733) (10 2619.4596153846 1108.5972850679) (10 2624.4343891403
1131.221719457))
((0 . "LWPOLYLINE") (100 . "AcDbEntity") (8 . "PLANTS") (62 . 94) (370 . 13) (100 . "AcDbPolyline") (90 . 3) (70 . 0)
(43 . 0.0) (10 2662.1415158371 1059.5786199095) (10 2628.2048642534 1059.7263574661) (10 2613.1221719457
1067.1182126697))
((0 . "LWPOLYLINE") (100 . "AcDbEntity") (8 . "PLANTS") (62 . 94) (370 . 13) (100 . "AcDbPolyline") (90 . 2) (70 . 0)
(43 . 0.0) (10 2620.6639140271 1138.7641402715) (10 2624.4343891403 1131.221719457))
((0 . "LWPOLYLINE") (100 . "AcDbEntity") (8 . "PLANTS") (62 . 94) (370 . 13) (100 . "AcDbPolyline") (90 . 3) (70 . 0)
(43 . 0.0) (10 2620.6639140271 1138.7641402715) (10 2625.6385746606 1153.8461538462) (10 2647.0588235294
1187.7828054299))
((0 . "LWPOLYLINE") (100 . "AcDbEntity") (8 . "PLANTS") (62 . 94) (370 . 13) (100 . "AcDbPolyline") (90 . 2) (70 . 0)
(43 . 0.0) (10 2624.4343891403 3993.2126696833) (10 2628.2048642534 3966.817081448))
((0 . "LWPOLYLINE") (100 . "AcDbEntity") (8 . "PLANTS") (62 . 94) (370 . 13) (100 . "AcDbPolyline") (90 . 3) (70 . 0)
(43 . 0.0) (10 2643.2883484163 4004.5248868778) (10 2631.9826923077 4003.3207013575) (10 2624.4343891403
3993.2126696833))
((0 . "LWPOLYLINE") (100 . "AcDbEntity") (8 . "PLANTS") (62 . 94) (370 . 13) (100 . "AcDbPolyline") (90 . 2) (70 . 0)
(43 . 0.0) (10 2624.4343891403 3891.4027149321) (10 2624.4343891403 3906.4860859729))
((0 . "LWPOLYLINE") (100 . "AcDbEntity") (8 . "PLANTS") (62 . 94) (370 . 13) (100 . "AcDbPolyline") (90 . 3) (70 . 0)
(43 . 0.0) (10 2658.371040724 3947.963800905) (10 2650.6748868778 3925.4874434389) (10 2624.4343891403 3906.4860859729))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2624.4343891403 3891.4027149321 0.0) (10 2644.6499231102 3889.4583095059 0.0) (10 2669.6584605923
3879.3048155344 0.0) (10 2688.5372171946 3891.4027149321 0.0))
((0 . "LWPOLYLINE") (100 . "AcDbEntity") (8 . "PLANTS") (62 . 94) (370 . 13) (100 . "AcDbPolyline") (90 . 2) (70 . 0)
(43 . 0.0) (10 2624.4343891403 1263.1985294118) (10 2624.4343891403 1278.2805429864))
((0 . "LWPOLYLINE") (100 . "AcDbEntity") (8 . "PLANTS") (62 . 94) (370 . 13) (100 . "AcDbPolyline") (90 . 3) (70 . 0)
(43 . 0.0) (10 2613.2739993055 1317.1086668992) (10 2613.2704751131 1300.9049773756) (10 2624.4343891403
1278.2805429864))
((0 . "LWPOLYLINE") (100 . "AcDbEntity") (8 . "PLANTS") (62 . 94) (370 . 13) (100 . "AcDbPolyline") (90 . 3) (70 . 0)
(43 . 0.0) (10 2624.4343891403 1278.2805429864) (10 2638.4610859729 1293.3625565611) (10 2645.4068396738
1311.639893809))
((0 . "LWPOLYLINE") (100 . "AcDbEntity") (8 . "PLANTS") (62 . 94) (370 . 13) (100 . "AcDbPolyline") (90 . 2) (70 . 0)
(43 . 0.0) (10 2650.8292986425 1240.5740950226) (10 2624.4343891403 1263.1985294118))
((0 . "LWPOLYLINE") (100 . "AcDbEntity") (8 . "PLANTS") (62 . 94) (370 . 13) (100 . "AcDbPolyline") (90 . 3) (70 . 0)
(43 . 0.0) (10 2686.6515837104 1127.4519230769) (10 2658.371040724 1123.8277149321) (10 2624.4343891403 1131.221719457))
((0 . "LWPOLYLINE") (100 . "AcDbEntity") (8 . "PLANTS") (62 . 94) (370 . 13) (100 . "AcDbPolyline") (90 . 3) (70 . 0)
(43 . 0.0) (10 2662.1415158371 6881.5985294118) (10 2639.5174208145 6873.0011312217) (10 2628.2048642534
6862.745361991))
((0 . "LWPOLYLINE") (100 . "AcDbEntity") (8 . "PLANTS") (62 . 94) (370 . 13) (100 . "AcDbPolyline") (90 . 2) (70 . 0)
(43 . 0.0) (10 2628.2048642534 4102.5636877828) (10 2628.2048642534 4149.4289269554))
((0 . "LWPOLYLINE") (100 . "AcDbEntity") (8 . "PLANTS") (62 . 94) (370 . 13) (100 . "AcDbPolyline") (90 . 3) (70 . 0)
(43 . 0.0) (10 2669.9485729385 4109.4889822796) (10 2647.0588235294 4102.7121040724) (10 2628.2048642534
4102.5636877828))
((0 . "LWPOLYLINE") (100 . "AcDbEntity") (8 . "PLANTS") (62 . 94) (370 . 13) (100 . "AcDbPolyline") (90 . 3) (70 . 0)
(43 . 0.0) (10 2658.371040724 3947.963800905) (10 2643.2883484163 3961.9904977376) (10 2628.2048642534 3966.817081448))
((0 . "LWPOLYLINE") (100 . "AcDbEntity") (8 . "PLANTS") (62 . 94) (370 . 13) (100 . "AcDbPolyline") (90 . 3) (70 . 0)
(43 . 0.0) (10 2631.9761312217 991.7053167421) (10 2730.0148190045 991.7101809955) (10 2741.3270361991 995.4751131222))
((0 . "LWPOLYLINE") (100 . "AcDbEntity") (8 . "PLANTS") (62 . 94) (370 . 13) (100 . "AcDbPolyline") (90 . 2) (70 . 0)
(43 . 0.0) (10 2639.517081448 6919.3064479638) (10 2707.3903846154 6934.3891402715))
((0 . "LWPOLYLINE") (100 . "AcDbEntity") (8 . "PLANTS") (62 . 94) (370 . 13) (100 . "AcDbPolyline") (90 . 2) (70 . 0)
(43 . 0.0) (10 2643.2883484163 4004.5248868778) (10 2643.2883484163 4015.8371040724))
((0 . "LWPOLYLINE") (100 . "AcDbEntity") (8 . "PLANTS") (62 . 94) (370 . 13) (100 . "AcDbPolyline") (90 . 3) (70 . 0)
(43 . 0.0) (10 2688.5372171946 4000.7537330317) (10 2650.836199095 4000.9021493213) (10 2643.2883484163
4004.5248868778))
((0 . "LWPOLYLINE") (100 . "AcDbEntity") (8 . "PLANTS") (62 . 94) (370 . 13) (100 . "AcDbPolyline") (90 . 3) (70 . 0)
(43 . 0.0) (10 2647.0588235294 4042.2326923077) (10 2658.37760181 4056.2593891403) (10 2684.7659502262 4064.8571266968))
((0 . "LWPOLYLINE") (100 . "AcDbEntity") (8 . "PLANTS") (62 . 94) (370 . 13) (100 . "AcDbPolyline") (90 . 2) (70 . 0)
(43 . 0.0) (10 2650.8292986425 1240.5740950226) (10 2647.0588235294 1187.7828054299))
((0 . "LWPOLYLINE") (100 . "AcDbEntity") (8 . "PLANTS") (62 . 94) (370 . 13) (100 . "AcDbPolyline") (90 . 3) (70 . 0)
(43 . 0.0) (10 2688.5372171946 1195.3252262443) (10 2665.9127828054 1187.9305429864) (10 2647.0588235294
1187.7828054299))
((0 . "LWPOLYLINE") (100 . "AcDbEntity") (8 . "PLANTS") (62 . 94) (370 . 13) (100 . "AcDbPolyline") (90 . 2) (70 . 0)
(43 . 0.0) (10 2650.8292986425 1240.5740950226) (10 2677.225 1240.5740950226))
((0 . "LWPOLYLINE") (100 . "AcDbEntity") (8 . "PLANTS") (62 . 94) (370 . 13) (100 . "AcDbPolyline") (90 . 2) (70 . 0)
(43 . 0.0) (10 2688.5372171946 3949.8487556561) (10 2658.371040724 3947.963800905))
((0 . "LWPOLYLINE") (100 . "AcDbEntity") (8 . "PLANTS") (62 . 94) (370 . 13) (100 . "AcDbPolyline") (90 . 2) (70 . 0)
(43 . 0.0) (10 2662.1415158371 1082.2030542986) (10 2662.1415158371 1059.5786199095))
((0 . "LWPOLYLINE") (100 . "AcDbEntity") (8 . "PLANTS") (62 . 94) (370 . 13) (100 . "AcDbPolyline") (90 . 2) (70 . 0)
(43 . 0.0) (10 2688.5372171946 1059.5786199095) (10 2662.1415158371 1059.5786199095))
((0 . "LWPOLYLINE") (100 . "AcDbEntity") (8 . "PLANTS") (62 . 94) (370 . 13) (100 . "AcDbPolyline") (90 . 3) (70 . 0)
(43 . 0.0) (10 2688.5372171946 1202.8648190045) (10 2682.1932126697 1210.4141402715) (10 2677.225 1240.5740950226))
((0 . "LWPOLYLINE") (100 . "AcDbEntity") (8 . "PLANTS") (62 . 94) (370 . 13) (100 . "AcDbPolyline") (90 . 2) (70 . 0)
(43 . 0.0) (10 2684.2155459342 1263.8753322578) (10 2677.225 1240.5740950226))
((0 . "LWPOLYLINE") (100 . "AcDbEntity") (8 . "PLANTS") (62 . 94) (370 . 13) (100 . "AcDbPolyline") (90 . 2) (70 . 0)
(43 . 0.0) (10 2689.8088994446 4085.0455035029) (10 2684.7659502262 4064.8571266968))
((0 . "LWPOLYLINE") (100 . "AcDbEntity") (8 . "PLANTS") (62 . 94) (370 . 13) (100 . "AcDbPolyline") (90 . 2) (70 . 0)
(43 . 0.0) (10 2688.5372171946 4046.00260181) (10 2684.7659502262 4064.8571266968))
((0 . "LWPOLYLINE") (100 . "AcDbEntity") (8 . "PLANTS") (62 . 94) (370 . 13) (100 . "AcDbPolyline") (90 . 2) (70 . 0)
(43 . 0.0) (10 2686.6515837104 1127.4519230769) (10 2699.8494343891 1093.5152714932))
((0 . "LWPOLYLINE") (100 . "AcDbEntity") (8 . "PLANTS") (62 . 94) (370 . 13) (100 . "AcDbPolyline") (90 . 3) (70 . 0)
(43 . 0.0) (10 2686.6515837104 1127.4519230769) (10 2685.82239819 1142.5270361991) (10 2692.3076923077 1150.0763574661))
((0 . "LWPOLYLINE") (100 . "AcDbEntity") (8 . "PLANTS") (62 . 94) (370 . 13) (100 . "AcDbPolyline") (90 . 2) (70 . 0)
(43 . 0.0) (10 2686.6515837104 1127.4519230769) (10 2714.9321266968 1134.9915158371))
((0 . "LWPOLYLINE") (100 . "AcDbEntity") (8 . "PLANTS") (62 . 94) (370 . 13) (100 . "AcDbPolyline") (90 . 2) (70 . 0)
(43 . 0.0) (10 2688.5372171946 4000.7537330317) (10 2688.5372171946 4046.00260181))
((0 . "LWPOLYLINE") (100 . "AcDbEntity") (8 . "PLANTS") (62 . 94) (370 . 13) (100 . "AcDbPolyline") (90 . 3) (70 . 0)
(43 . 0.0) (10 2713.1163388361 4056.3594242518) (10 2711.1616515837 4054.7421945701) (10 2688.5372171946 4046.00260181))
((0 . "LWPOLYLINE") (100 . "AcDbEntity") (8 . "PLANTS") (62 . 94) (370 . 13) (100 . "AcDbPolyline") (90 . 2) (70 . 0)
(43 . 0.0) (10 2688.5372171946 4000.7537330317) (10 2688.5372171946 3949.8487556561))
((0 . "LWPOLYLINE") (100 . "AcDbEntity") (8 . "PLANTS") (62 . 94) (370 . 13) (100 . "AcDbPolyline") (90 . 3) (70 . 0)
(43 . 0.0) (10 2688.5372171946 4000.7537330317) (10 2718.70260181 4000.9087104072) (10 2730.0148190045 4012.0659502262))
((0 . "LWPOLYLINE") (100 . "AcDbEntity") (8 . "PLANTS") (62 . 94) (370 . 13) (100 . "AcDbPolyline") (90 . 2) (70 . 0)
(43 . 0.0) (10 2688.5372171946 3949.8487556561) (10 2688.5372171946 3891.4027149321))
((0 . "LWPOLYLINE") (100 . "AcDbEntity") (8 . "PLANTS") (62 . 94) (370 . 13) (100 . "AcDbPolyline") (90 . 2) (70 . 0)
(43 . 0.0) (10 2688.5372171946 3949.8487556561) (10 2714.9321266968 3951.7349547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2688.5372171946 3891.4027149321 0.0) (10 2707.5741369346 3883.9568707868 0.0) (10 2733.5788188396
3875.639600228 0.0) (10 2752.6392533937 3887.631561086 0.0))
((0 . "LWPOLYLINE") (100 . "AcDbEntity") (8 . "PLANTS") (62 . 94) (370 . 13) (100 . "AcDbPolyline") (90 . 2) (70 . 0)
(43 . 0.0) (10 2688.5372171946 1195.3252262443) (10 2688.5372171946 1202.8648190045))
((0 . "LWPOLYLINE") (100 . "AcDbEntity") (8 . "PLANTS") (62 . 94) (370 . 13) (100 . "AcDbPolyline") (90 . 3) (70 . 0)
(43 . 0.0) (10 2721.1241584021 1218.4493476819) (10 2707.3903846154 1207.8346153846) (10 2688.5372171946
1202.8648190045))
((0 . "LWPOLYLINE") (100 . "AcDbEntity") (8 . "PLANTS") (62 . 94) (370 . 13) (100 . "AcDbPolyline") (90 . 2) (70 . 0)
(43 . 0.0) (10 2688.5372171946 1195.3252262443) (10 2692.3076923077 1150.0763574661))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2748.8687782805 1059.5786199095 0.0) (10 2734.5990387096 1041.9350925116 0.0) (10 2705.4512523344
1051.0631954561 0.0) (10 2688.5372171946 1059.5786199095 0.0))
((0 . "LWPOLYLINE") (100 . "AcDbEntity") (8 . "PLANTS") (62 . 94) (370 . 13) (100 . "AcDbPolyline") (90 . 2) (70 . 0)
(43 . 0.0) (10 2699.8494343891 1093.5152714932) (10 2688.5372171946 1059.5786199095))
((0 . "LWPOLYLINE") (100 . "AcDbEntity") (8 . "PLANTS") (62 . 94) (370 . 13) (100 . "AcDbPolyline") (90 . 2) (70 . 0)
(43 . 0.0) (10 2714.9321266968 1150.0763574661) (10 2692.3076923077 1150.0763574661))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3278321564) (40
. 1) (40 . 1) (40 . 1) (40 . 1) (10 2696.0781674208 6885.36979638 0.0) (10 2705.4628388692 6889.5978046177 0.0) (10
2731.2655963816 6905.313382985 0.0) (10 2765.2275940485 6897.6386873581 0.0) (10 2779.0349547511 6919.3064479638 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2699.8494343891 1093.5152714932 0.0) (10 2724.8066511272 1102.9510160734 0.0) (10 2747.9537279559
1082.9567212973 0.0) (10 2748.8687782805 1059.5786199095 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2714.9321266968 6787.3303167421 0.0) (10 2715.6472987692 6764.8637730027 0.0) (10 2725.4977194235
6732.7800188553 0.0) (10 2752.74257346 6730.7692307692 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4869391106)
(40 . 0.6066076387) (40 . 1) (40 . 1) (40 . 1) (40 . 1) (10 2771.4932126697 6847.661877828 0.0) (10 2752.1726290403
6833.5278523429 0.0) (10 2691.1962757111 6862.2315167683 0.0) (10 2662.3962183983 6824.816888389 0.0) (10
2689.7936720094 6779.0064443621 0.0) (10 2714.9321266969 6787.3303167421 0.0))
((0 . "LWPOLYLINE") (100 . "AcDbEntity") (8 . "PLANTS") (62 . 94) (370 . 13) (100 . "AcDbPolyline") (90 . 3) (70 . 0)
(43 . 0.0) (10 2714.9321266968 6787.3303167421) (10 2730.0148190045 6791.1007918552) (10 2997.7375565611
6787.3303167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2714.9321266968 3951.7349547511 0.0) (10 2721.1220075938 3926.3885517917 0.0) (10 2753.4105312285
3915.9007654999 0.0) (10 2752.6392533937 3887.631561086 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2714.9321266968 3951.7349547511 0.0) (10 2719.2879730132 3966.4387500464 0.0) (10 2749.6562823173
3975.173246964 0.0) (10 2756.410520362 3959.2760180996 0.0))
((0 . "LWPOLYLINE") (100 . "AcDbEntity") (8 . "PLANTS") (62 . 94) (370 . 13) (100 . "AcDbPolyline") (90 . 2) (70 . 0)
(43 . 0.0) (10 2714.9321266968 1150.0763574661) (10 2714.9321266968 1134.9915158371))
((0 . "LWPOLYLINE") (100 . "AcDbEntity") (8 . "PLANTS") (62 . 94) (370 . 13) (100 . "AcDbPolyline") (90 . 2) (70 . 0)
(43 . 0.0) (10 2714.9321266968 1150.0763574661) (10 2733.7860859729 1157.6159502262))
((0 . "LWPOLYLINE") (100 . "AcDbEntity") (8 . "PLANTS") (62 . 94) (370 . 13) (100 . "AcDbPolyline") (90 . 2) (70 . 0)
(43 . 0.0) (10 2748.8687782805 1123.6792986425) (10 2714.9321266968 1134.9915158371))
((0 . "LWPOLYLINE") (100 . "AcDbEntity") (8 . "PLANTS") (62 . 94) (370 . 13) (100 . "AcDbPolyline") (90 . 2) (70 . 0)
(43 . 0.0) (10 2748.8687782805 1150.0763574661) (10 2733.7860859729 1157.6159502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2751.7244332254 1180.7874709763 0.0) (10 2740.8616336206 1180.1117661217 0.0) (10 2730.9654507185
1168.780643791 0.0) (10 2733.7860859729 1157.6159502262 0.0))
((0 . "LWPOLYLINE") (100 . "AcDbEntity") (8 . "PLANTS") (62 . 94) (370 . 13) (100 . "AcDbPolyline") (90 . 3) (70 . 0)
(43 . 0.0) (10 2812.9716063348 7013.5746606335) (10 2745.0983031674 7054.0031674208) (10 2741.0753924246
7055.2492505823))
((0 . "LWPOLYLINE") (100 . "AcDbEntity") (8 . "PLANTS") (62 . 94) (370 . 13) (100 . "AcDbPolyline") (90 . 2) (70 . 0)
(43 . 0.0) (10 2718.7135615988 7036.8427039693) (10 2741.3270361991 7017.3451357466))
((0 . "LWPOLYLINE") (100 . "AcDbEntity") (8 . "PLANTS") (62 . 94) (370 . 13) (100 . "AcDbPolyline") (90 . 3) (70 . 0)
(43 . 0.0) (10 2741.3270361991 6941.9308823529) (10 2752.6395927602 6940.7331447964) (10 2779.0349547511
6919.3064479638))
((0 . "LWPOLYLINE") (100 . "AcDbEntity") (8 . "PLANTS") (62 . 94) (370 . 13) (100 . "AcDbPolyline") (90 . 2) (70 . 0)
(43 . 0.0) (10 2776.6772129525 1150.0763574661) (10 2748.8687782805 1150.0763574661))
((0 . "LWPOLYLINE") (100 . "AcDbEntity") (8 . "PLANTS") (62 . 94) (370 . 13) (100 . "AcDbPolyline") (90 . 2) (70 . 0)
(43 . 0.0) (10 2748.8687782805 1150.0763574661) (10 2748.8687782805 1123.6792986425))
((0 . "LWPOLYLINE") (100 . "AcDbEntity") (8 . "PLANTS") (62 . 94) (370 . 13) (100 . "AcDbPolyline") (90 . 3) (70 . 0)
(43 . 0.0) (10 2782.8054298643 1113.574183269) (10 2760.1809954751 1117.195361991) (10 2748.8687782805 1123.6792986425))
((0 . "LWPOLYLINE") (100 . "AcDbEntity") (8 . "PLANTS") (62 . 94) (370 . 13) (100 . "AcDbPolyline") (90 . 2) (70 . 0)
(43 . 0.0) (10 2782.8054298643 1059.5786199095) (10 2748.8687782805 1059.5786199095))
((0 . "LWPOLYLINE") (100 . "AcDbEntity") (8 . "PLANTS") (62 . 94) (370 . 13) (100 . "AcDbPolyline") (90 . 2) (70 . 0)
(43 . 0.0) (10 2756.410520362 3959.2760180995) (10 2752.6392533937 3947.963800905))
((0 . "LWPOLYLINE") (100 . "AcDbEntity") (8 . "PLANTS") (62 . 94) (370 . 13) (100 . "AcDbPolyline") (90 . 3) (70 . 0)
(43 . 0.0) (10 2752.6392533937 3887.631561086) (10 2760.1875565611 3884.0095022624) (10 2782.8054298643
3883.8986232649))
((0 . "LWPOLYLINE") (100 . "AcDbEntity") (8 . "PLANTS") (62 . 94) (370 . 13) (100 . "AcDbPolyline") (90 . 2) (70 . 0)
(43 . 0.0) (10 2782.8054298643 3959.2760180995) (10 2756.410520362 3959.2760180995))
((0 . "LWPOLYLINE") (100 . "AcDbEntity") (8 . "PLANTS") (62 . 94) (370 . 13) (100 . "AcDbPolyline") (90 . 3) (70 . 0)
(43 . 0.0) (10 2760.1809954751 6994.7207013575) (10 2786.5759049774 6969.3817873303) (10 2812.9716063348
6960.7840497738))
((0 . "LWPOLYLINE") (100 . "AcDbEntity") (8 . "PLANTS") (62 . 94) (370 . 13) (100 . "AcDbPolyline") (90 . 2) (70 . 0)
(43 . 0.0) (10 2771.4932126697 6847.6618778281) (10 2775.2636877828 6874.0575791855))
((0 . "LWPOLYLINE") (100 . "AcDbEntity") (8 . "PLANTS") (62 . 94) (370 . 13) (100 . "AcDbPolyline") (90 . 3) (70 . 0)
(43 . 0.0) (10 2771.4932126697 6847.6618778281) (10 2812.9716063348 6847.8167420814) (10 2831.8247737557
6858.9740950226))
((0 . "LWPOLYLINE") (100 . "AcDbEntity") (8 . "PLANTS") (62 . 94) (370 . 13) (100 . "AcDbPolyline") (90 . 2) (70 . 0)
(43 . 0.0) (10 2771.4932126697 935.1442307692) (10 2782.8054298643 935.1442307692))
((0 . "LWPOLYLINE") (100 . "AcDbEntity") (8 . "PLANTS") (62 . 94) (370 . 13) (100 . "AcDbPolyline") (90 . 2) (70 . 0)
(43 . 0.0) (10 2803.5442307692 6915.5351809955) (10 2779.0349547511 6919.3064479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2718.7487158456 3744.3438914027 0.0) (10 2693.8216136759 3804.8433919919 0.0) (10 2745.3008066003
3795.3328450511 0.0) (10 2782.8054298643 3794.7191055738 0.0))
((0 . "LWPOLYLINE") (100 . "AcDbEntity") (8 . "PLANTS") (62 . 94) (370 . 13) (100 . "AcDbPolyline") (90 . 2) (70 . 0)
(43 . 0.0) (10 2801.6585864879 226.2024479878) (10 2801.6564101926 348.7757160255))
((0 . "LWPOLYLINE") (100 . "AcDbEntity") (8 . "PLANTS") (62 . 94) (370 . 13) (100 . "AcDbPolyline") (90 . 3) (70 . 0)
(43 . 0.0) (10 2805.4298642534 6900.4524886878) (10 2801.6593891403 6904.2229638009) (10 2803.5442307692
6915.5351809955))
((0 . "LWPOLYLINE") (100 . "AcDbEntity") (8 . "PLANTS") (62 . 94) (370 . 13) (100 . "AcDbPolyline") (90 . 2) (70 . 0)
(43 . 0.0) (10 2816.742081448 6941.9308823529) (10 2803.5442307692 6915.5351809955))
((0 . "LWPOLYLINE") (100 . "AcDbEntity") (8 . "PLANTS") (62 . 94) (370 . 13) (100 . "AcDbPolyline") (90 . 3) (70 . 0)
(43 . 0.0) (10 2835.596040724 6934.3891402715) (10 2824.2772624434 6920.3624434389) (10 2803.5442307692
6915.5351809955))
((0 . "LWPOLYLINE") (100 . "AcDbEntity") (8 . "PLANTS") (62 . 94) (370 . 13) (100 . "AcDbPolyline") (90 . 2) (70 . 0)
(43 . 0.0) (10 2820.5125565611 7013.5746606335) (10 2812.9716063348 7013.5746606335))
((0 . "LWPOLYLINE") (100 . "AcDbEntity") (8 . "PLANTS") (62 . 94) (370 . 13) (100 . "AcDbPolyline") (90 . 3) (70 . 0)
(43 . 0.0) (10 2820.5125565611 6987.1797511312) (10 2813.3331447964 6991.1708144796) (10 2812.9716063348
7013.5746606335))
((0 . "LWPOLYLINE") (100 . "AcDbEntity") (8 . "PLANTS") (62 . 94) (370 . 13) (100 . "AcDbPolyline") (90 . 2) (70 . 0)
(43 . 0.0) (10 2816.742081448 6941.9308823529) (10 2812.9716063348 6960.7840497738))
((0 . "LWPOLYLINE") (100 . "AcDbEntity") (8 . "PLANTS") (62 . 94) (370 . 13) (100 . "AcDbPolyline") (90 . 2) (70 . 0)
(43 . 0.0) (10 2820.5125565611 6987.1797511312) (10 2812.9716063348 6960.7840497738))
((0 . "LWPOLYLINE") (100 . "AcDbEntity") (8 . "PLANTS") (62 . 94) (370 . 13) (100 . "AcDbPolyline") (90 . 3) (70 . 0)
(43 . 0.0) (10 2835.596040724 6934.3891402715) (10 2828.0477375566 6940.7331447964) (10 2816.742081448 6941.9308823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2816.742081448 6734.5397058824 0.0) (10 2872.0098428182 6560.7299817774 0.0) (10 2935.1616302864
6766.8379172305 0.0) (10 2990.1961538462 6734.5397058824 0.0))
((0 . "LWPOLYLINE") (100 . "AcDbEntity") (8 . "PLANTS") (62 . 94) (370 . 13) (100 . "AcDbPolyline") (90 . 3) (70 . 0)
(43 . 0.0) (10 2831.8247737557 6987.1797511312) (10 2826.8631221719 7006.0263574661) (10 2820.5125565611
7013.5746606335))
((0 . "SPLINE") (100 . "AcDbEntity") (8 . "PLANTS") (62 . 94) (370 . 13) (100 . "AcDbSpline") (70 . 0) (71 . 3) (72 .
12) (73 . 8) (74 . 0) (42 . 0.0000001) (43 . 0.0000001) (40 . 0.0) (40 . 0.0) (40 . 0.0) (40 . 0.0) (40 . 0.2494499188)
(40 . 0.3168803121) (40 . 0.6286593782) (40 . 0.7562669187) (40 . 1) (40 . 1) (40 . 1) (40 . 1) (10 2820.5125565612
7013.5746606335 0.0) (10 2830.2610639683 7033.3246831362 0.0) (10 2796.8889370268 7074.747018983 0.0) (10
2843.8780368108 7087.9548031507 0.0) (10 2891.8086432577 7051.5162276453 0.0) (10 2928.5809307218 7007.4096623129 0.0)
(10 2935.2730199116 6970.5154350892 0.0) (10 2960.0300904977 6964.5553167421 0.0))
((0 . "LWPOLYLINE") (100 . "AcDbEntity") (8 . "PLANTS") (62 . 94) (370 . 13) (100 . "AcDbPolyline") (90 . 2) (70 . 0)
(43 . 0.0) (10 2831.8247737557 6987.1797511312) (10 2820.5125565611 6987.1797511312))
((0 . "LWPOLYLINE") (100 . "AcDbEntity") (8 . "PLANTS") (62 . 94) (370 . 13) (100 . "AcDbPolyline") (90 . 3) (70 . 0)
(43 . 0.0) (10 2831.8247737557 6987.1797511312) (10 2849.6227375566 6975.8606334842) (10 2861.9909502262
6941.9308823529))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4622382589) (40
. 1) (40 . 1) (40 . 1) (40 . 1) (10 2961.9156108597 6872.1719457013 0.0) (10 2947.8307264555 6858.6401388688 0.0) (10
2900.785096061 6840.5488962014 0.0) (10 2849.8442027397 6842.4962422178 0.0) (10 2831.8247737557 6858.9740950225 0.0))
((0 . "LWPOLYLINE") (100 . "AcDbEntity") (8 . "PLANTS") (62 . 94) (370 . 13) (100 . "AcDbPolyline") (90 . 3) (70 . 0)
(43 . 0.0) (10 2854.4492081448 6892.9107466063) (10 2840.4225113122 6877.8214932127) (10 2831.8247737557
6858.9740950226))
((0 . "LWPOLYLINE") (100 . "AcDbEntity") (8 . "PLANTS") (62 . 94) (370 . 13) (100 . "AcDbPolyline") (90 . 2) (70 . 0)
(43 . 0.0) (10 2835.596040724 6934.3891402715) (10 2843.1369909502 6934.3891402715))
((0 . "LWPOLYLINE") (100 . "AcDbEntity") (8 . "PLANTS") (62 . 94) (370 . 13) (100 . "AcDbPolyline") (90 . 2) (70 . 0)
(43 . 0.0) (10 2858.2204751131 230.0141402715) (10 2835.596040724 233.7867647059))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2839.3665158371 324.2845022624 0.0) (10 2863.5708697241 334.0006837731 0.0) (10 2870.8516515422
300.8613479694 0.0) (10 2892.1567873303 301.6600678733 0.0))
((0 . "LWPOLYLINE") (100 . "AcDbEntity") (8 . "PLANTS") (62 . 94) (370 . 13) (100 . "AcDbPolyline") (90 . 3) (70 . 0)
(43 . 0.0) (10 2854.4492081448 6892.9107466063) (10 2850.5304298643 6919.3064479638) (10 2843.1369909502
6934.3891402715))
((0 . "LWPOLYLINE") (100 . "AcDbEntity") (8 . "PLANTS") (62 . 94) (370 . 13) (100 . "AcDbPolyline") (90 . 2) (70 . 0)
(43 . 0.0) (10 2861.9909502262 6941.9308823529) (10 2843.1369909502 6934.3891402715))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.8024788834) (40
. 1) (40 . 1) (40 . 1) (40 . 1) (10 2843.1369909503 444.9462669683 0.0) (10 2884.5323197211 406.6237508969 0.0) (10
2956.3513499167 348.1636209869 0.0) (10 2960.342877526 272.2138738957 0.0) (10 2948.7178733033 260.180995475 0.0))
((0 . "LWPOLYLINE") (100 . "AcDbEntity") (8 . "PLANTS") (62 . 94) (370 . 13) (100 . "AcDbPolyline") (90 . 3) (70 . 0)
(43 . 0.0) (10 2854.4492081448 6892.9107466063) (10 2865.7614253394 6892.9107466063) (10 2869.5326923077
6896.6820135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2998.366297503 786.7479634069 0.0) (10 3023.6329729106 796.820053358 0.0) (10 3046.5130883209
779.2288007482 0.0) (10 3071.5064390177 784.2867388207 0.0))
((0 . "LWPOLYLINE") (100 . "AcDbEntity") (8 . "PLANTS") (62 . 94) (370 . 13) (100 . "AcDbPolyline") (90 . 3) (70 . 0)
(43 . 0.0) (10 2858.2204751131 7021.1164027149) (10 2907.0917420814 6964.5553167421) (10 2918.5520361991
6945.7013574661))
((0 . "LWPOLYLINE") (100 . "AcDbEntity") (8 . "PLANTS") (62 . 94) (370 . 13) (100 . "AcDbPolyline") (90 . 2) (70 . 0)
(43 . 0.0) (10 2858.2204751131 230.0141402715) (10 2857.680180726 226.0779555562))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2858.2204751131 230.0141402715 0.0) (10 2887.4401581813 244.9182410475 0.0) (10 2926.0123087262
216.9011870923 0.0) (10 2948.7178733032 248.8687782805 0.0))
((0 . "LWPOLYLINE") (100 . "AcDbEntity") (8 . "PLANTS") (62 . 94) (370 . 13) (100 . "AcDbPolyline") (90 . 3) (70 . 0)
(43 . 0.0) (10 2914.7812217195 6926.84739819) (10 2884.6153846154 6928.0516968326) (10 2861.9909502262 6941.9308823529))
((0 . "LWPOLYLINE") (100 . "AcDbEntity") (8 . "PLANTS") (62 . 94) (370 . 13) (100 . "AcDbPolyline") (90 . 2) (70 . 0)
(43 . 0.0) (10 2907.2398190045 320.5118778281) (10 2877.0736425339 365.7607466063))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2892.1567873303 301.6600678733 0.0) (10 2900.8914043088 285.5189767402 0.0) (10 2917.75508254
258.986585088 0.0) (10 2941.1764705882 263.9507918552 0.0))
((0 . "LWPOLYLINE") (100 . "AcDbEntity") (8 . "PLANTS") (62 . 94) (370 . 13) (100 . "AcDbPolyline") (90 . 2) (70 . 0)
(43 . 0.0) (10 2907.2398190045 320.5118778281) (10 2892.1567873303 301.6600678733))
((0 . "LWPOLYLINE") (100 . "AcDbEntity") (8 . "PLANTS") (62 . 94) (370 . 13) (100 . "AcDbPolyline") (90 . 3) (70 . 0)
(43 . 0.0) (10 2907.2398190045 426.0944570136) (10 2929.8708144796 399.69739819) (10 2944.9472850679 388.3851809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2907.2398190045 320.5118778281 0.0) (10 2933.0660095468 317.7751302184 0.0) (10 2929.0908281591
277.1778672062 0.0) (10 2941.1764705882 263.9507918552 0.0))
((0 . "LWPOLYLINE") (100 . "AcDbEntity") (8 . "PLANTS") (62 . 94) (370 . 13) (100 . "AcDbPolyline") (90 . 3) (70 . 0)
(43 . 0.0) (10 2961.9156108597 6872.1719457014) (10 2922.47760181 6911.7647058824) (10 2914.7812217195 6926.84739819))
((0 . "LWPOLYLINE") (100 . "AcDbEntity") (8 . "PLANTS") (62 . 94) (370 . 13) (100 . "AcDbPolyline") (90 . 2) (70 . 0)
(43 . 0.0) (10 2914.7812217195 6926.84739819) (10 2918.5520361991 6945.7013574661))
((0 . "LWPOLYLINE") (100 . "AcDbEntity") (8 . "PLANTS") (62 . 94) (370 . 13) (100 . "AcDbPolyline") (90 . 3) (70 . 0)
(43 . 0.0) (10 2960.0300904977 6945.7013574661) (10 2948.7178733032 6941.9440045249) (10 2918.5520361991
6945.7013574661))
((0 . "LWPOLYLINE") (100 . "AcDbEntity") (8 . "PLANTS") (62 . 94) (370 . 13) (100 . "AcDbPolyline") (90 . 2) (70 . 0)
(43 . 0.0) (10 2937.4056561086 7070.1357466063) (10 2929.8642533937 7073.9062217195))
((0 . "LWPOLYLINE") (100 . "AcDbEntity") (8 . "PLANTS") (62 . 94) (370 . 13) (100 . "AcDbPolyline") (90 . 2) (70 . 0)
(43 . 0.0) (10 2941.1764705882 263.9507918552) (10 2948.7178733032 260.1809954751))
((0 . "LWPOLYLINE") (100 . "AcDbEntity") (8 . "PLANTS") (62 . 94) (370 . 13) (100 . "AcDbPolyline") (90 . 2) (70 . 0)
(43 . 0.0) (10 2944.9472850679 388.3851809955) (10 2944.9472850679 373.3031674208))
((0 . "LWPOLYLINE") (100 . "AcDbEntity") (8 . "PLANTS") (62 . 94) (370 . 13) (100 . "AcDbPolyline") (90 . 2) (70 . 0)
(43 . 0.0) (10 2944.9472850679 388.3851809955) (10 2956.2595022624 392.1578054299))
((0 . "LWPOLYLINE") (100 . "AcDbEntity") (8 . "PLANTS") (62 . 94) (370 . 13) (100 . "AcDbPolyline") (90 . 2) (70 . 0)
(43 . 0.0) (10 3008.5681051333 840.9312393166) (10 2982.7755789282 843.2643182404))
((0 . "LWPOLYLINE") (100 . "AcDbEntity") (8 . "PLANTS") (62 . 94) (370 . 13) (100 . "AcDbPolyline") (90 . 2) (70 . 0)
(43 . 0.0) (10 2948.7178733032 248.8687782805) (10 2948.7178733032 260.1809954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3046.757239819 252.6385746606 0.0) (10 3023.2834714162 223.1411654986 0.0) (10 2976.4225585547
231.8227742874 0.0) (10 2948.7178733032 248.8687782805 0.0))
((0 . "LWPOLYLINE") (100 . "AcDbEntity") (8 . "PLANTS") (62 . 94) (370 . 13) (100 . "AcDbPolyline") (90 . 2) (70 . 0)
(43 . 0.0) (10 2956.2595022624 399.69739819) (10 2956.2595022624 392.1578054299))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7576779478) (40
. 1) (40 . 1) (40 . 1) (40 . 1) (10 2997.7375565611 271.4932126697 0.0) (10 2993.0795329032 303.2854812718 0.0) (10
2974.1740366337 345.6054054488 0.0) (10 2965.1347958818 386.329050043 0.0) (10 2956.2595022625 392.1578054299 0.0))
((0 . "LWPOLYLINE") (100 . "AcDbEntity") (8 . "PLANTS") (62 . 94) (370 . 13) (100 . "AcDbPolyline") (90 . 2) (70 . 0)
(43 . 0.0) (10 2960.0300904977 6964.5553167421) (10 2960.0300904977 6945.7013574661))
((0 . "LWPOLYLINE") (100 . "AcDbEntity") (8 . "PLANTS") (62 . 94) (370 . 13) (100 . "AcDbPolyline") (90 . 3) (70 . 0)
(43 . 0.0) (10 2960.0300904977 6964.5553167421) (10 2966.3742081448 6972.1031674208) (10 2967.571719457
6990.9502262443))
((0 . "LWPOLYLINE") (100 . "AcDbEntity") (8 . "PLANTS") (62 . 94) (370 . 13) (100 . "AcDbPolyline") (90 . 2) (70 . 0)
(43 . 0.0) (10 2967.571719457 6941.9308823529) (10 2960.0300904977 6945.7013574661))
((0 . "LWPOLYLINE") (100 . "AcDbEntity") (8 . "PLANTS") (62 . 94) (370 . 13) (100 . "AcDbPolyline") (90 . 2) (70 . 0)
(43 . 0.0) (10 2961.9156108597 6872.1719457014) (10 2993.9667420814 6870.2863122172))
((0 . "LWPOLYLINE") (100 . "AcDbEntity") (8 . "PLANTS") (62 . 94) (370 . 13) (100 . "AcDbPolyline") (90 . 2) (70 . 0)
(43 . 0.0) (10 2961.9156108597 6872.1719457014) (10 2967.571719457 6941.9308823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 2963.8009049774 7047.5113122172 0.0) (10 2994.5628349085 7053.1409673107 0.0) (10 3022.1054948152
7022.8336444939 0.0) (10 3027.9033936652 6994.7207013575 0.0))
((0 . "LWPOLYLINE") (100 . "AcDbEntity") (8 . "PLANTS") (62 . 94) (370 . 13) (100 . "AcDbPolyline") (90 . 3) (70 . 0)
(43 . 0.0) (10 2963.8009049774 7047.5113122172) (10 2963.9489819005 7002.2624434389) (10 2967.571719457
6990.9502262443))
((0 . "LWPOLYLINE") (100 . "AcDbEntity") (8 . "PLANTS") (62 . 94) (370 . 13) (100 . "AcDbPolyline") (90 . 2) (70 . 0)
(43 . 0.0) (10 2963.8009049774 7047.5113122172) (10 2964.6245543032 7171.8835959103))
((0 . "LWPOLYLINE") (100 . "AcDbEntity") (8 . "PLANTS") (62 . 94) (370 . 13) (100 . "AcDbPolyline") (90 . 2) (70 . 0)
(43 . 0.0) (10 3003.3936651584 6977.7523755656) (10 2967.571719457 6990.9502262443))
((0 . "LWPOLYLINE") (100 . "AcDbEntity") (8 . "PLANTS") (62 . 94) (370 . 13) (100 . "AcDbPolyline") (90 . 2) (70 . 0)
(43 . 0.0) (10 2967.571719457 6941.9308823529) (10 2975.1131221719 6941.9308823529))
((0 . "LWPOLYLINE") (100 . "AcDbEntity") (8 . "PLANTS") (62 . 94) (370 . 13) (100 . "AcDbPolyline") (90 . 3) (70 . 0)
(43 . 0.0) (10 2971.3423076923 505.2799773756) (10 3011.7642533937 426.0944570136) (10 3012.8205882353 399.69739819))
((0 . "LWPOLYLINE") (100 . "AcDbEntity") (8 . "PLANTS") (62 . 94) (370 . 13) (100 . "AcDbPolyline") (90 . 3) (70 . 0)
(43 . 0.0) (10 3016.5911764706 6907.9942307692) (10 2997.7375565611 6930.463800905) (10 2975.1131221719
6941.9308823529))
((0 . "LWPOLYLINE") (100 . "AcDbEntity") (8 . "PLANTS") (62 . 94) (370 . 13) (100 . "AcDbPolyline") (90 . 2) (70 . 0)
(43 . 0.0) (10 3003.3936651584 6977.7523755656) (10 2975.1131221719 6941.9308823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3001.5083710407 392.1578054299 0.0) (10 2982.4064109987 398.6484147497 0.0) (10 2977.8635929013
424.3028446369 0.0) (10 2975.1131221719 441.1764705882 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5032449858) (40
. 1) (40 . 1) (40 . 1) (40 . 1) (10 3137.2549773756 6843.891402715 0.0) (10 3116.5908263453 6892.3478578231 0.0) (10
3075.1491174333 6826.3806909202 0.0) (10 3008.8587302836 6843.9118375256 0.0) (10 2993.9667420814 6870.2863122172 0.0))
((0 . "LWPOLYLINE") (100 . "AcDbEntity") (8 . "PLANTS") (62 . 94) (370 . 13) (100 . "AcDbPolyline") (90 . 3) (70 . 0)
(43 . 0.0) (10 2993.9667420814 6870.2863122172) (10 3011.7642533937 6892.9107466063) (10 3016.5911764706
6907.9942307692))
((0 . "LWPOLYLINE") (100 . "AcDbEntity") (8 . "PLANTS") (62 . 94) (370 . 13) (100 . "AcDbPolyline") (90 . 2) (70 . 0)
(43 . 0.0) (10 3005.278959276 6787.3303167421) (10 2997.7375565611 6787.3303167421))
((0 . "LWPOLYLINE") (100 . "AcDbEntity") (8 . "PLANTS") (62 . 94) (370 . 13) (100 . "AcDbPolyline") (90 . 3) (70 . 0)
(43 . 0.0) (10 3005.278959276 6787.3303167421) (10 3001.5083710407 6779.7885746606) (10 2997.7375565611
6787.3303167421))
((0 . "LWPOLYLINE") (100 . "AcDbEntity") (8 . "PLANTS") (62 . 94) (370 . 13) (100 . "AcDbPolyline") (90 . 3) (70 . 0)
(43 . 0.0) (10 3001.5083710407 392.1578054299) (10 3002.564479638 350.6787330317) (10 3020.3619909502 316.742081448))
((0 . "LWPOLYLINE") (100 . "AcDbEntity") (8 . "PLANTS") (62 . 94) (370 . 13) (100 . "AcDbPolyline") (90 . 2) (70 . 0)
(43 . 0.0) (10 3001.5083710407 392.1578054299) (10 3012.8205882353 399.69739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3042.9864253394 6972.0962669683 0.0) (10 3035.1189225305 6955.6591311969 0.0) (10 3007.2026366929
6956.4625854668 0.0) (10 3003.3936651584 6977.7523755656 0.0))
((0 . "LWPOLYLINE") (100 . "AcDbEntity") (8 . "PLANTS") (62 . 94) (370 . 13) (100 . "AcDbPolyline") (90 . 2) (70 . 0)
(43 . 0.0) (10 3003.3936651584 6977.7523755656) (10 3027.9033936652 6994.7207013575))
((0 . "LWPOLYLINE") (100 . "AcDbEntity") (8 . "PLANTS") (62 . 94) (370 . 13) (100 . "AcDbPolyline") (90 . 3) (70 . 0)
(43 . 0.0) (10 3005.278959276 6787.3303167421) (10 3016.5915158371 6794.7171945701) (10 3035.4450226244
6791.1007918552))
((0 . "LWPOLYLINE") (100 . "AcDbEntity") (8 . "PLANTS") (62 . 94) (370 . 13) (100 . "AcDbPolyline") (90 . 3) (70 . 0)
(43 . 0.0) (10 3024.1328054299 365.7607466063) (10 3023.0830316742 380.8455882353) (10 3012.8205882353 399.69739819))
((0 . "LWPOLYLINE") (100 . "AcDbEntity") (8 . "PLANTS") (62 . 94) (370 . 13) (100 . "AcDbPolyline") (90 . 3) (70 . 0)
(43 . 0.0) (10 3016.5911764706 6907.9942307692) (10 3058.0694570136 6920.3624434389) (10 3080.6938914027
6938.1596153846))
((0 . "LWPOLYLINE") (100 . "AcDbEntity") (8 . "PLANTS") (62 . 94) (370 . 13) (100 . "AcDbPolyline") (90 . 2) (70 . 0)
(43 . 0.0) (10 3020.3619909502 316.742081448) (10 3035.4450226244 316.742081448))
((0 . "LWPOLYLINE") (100 . "AcDbEntity") (8 . "PLANTS") (62 . 94) (370 . 13) (100 . "AcDbPolyline") (90 . 3) (70 . 0)
(43 . 0.0) (10 3046.757239819 252.6385746606) (10 3025.1892533937 282.8054298643) (10 3020.3619909502 316.742081448))
((0 . "LWPOLYLINE") (100 . "AcDbEntity") (8 . "PLANTS") (62 . 94) (370 . 13) (100 . "AcDbPolyline") (90 . 2) (70 . 0)
(43 . 0.0) (10 3039.2156108597 6994.7207013575) (10 3027.9033936652 6994.7207013575))
((0 . "SPLINE") (100 . "AcDbEntity") (8 . "PLANTS") (62 . 94) (370 . 13) (100 . "AcDbSpline") (70 . 0) (71 . 3) (72 .
13) (73 . 9) (74 . 0) (42 . 0.0000001) (43 . 0.0000001) (40 . 0.0) (40 . 0.0) (40 . 0.0) (40 . 0.0) (40 . 0.2236876833)
(40 . 0.4546776189) (40 . 0.5703234002) (40 . 0.6400493862) (40 . 0.8019244036) (40 . 1) (40 . 1) (40 . 1) (40 . 1) (10
3076.9230769231 7002.2624434389 0.0) (10 3094.5252014195 7020.7568930001 0.0) (10 3072.1630115262 7053.461103113 0.0)
(10 3087.8175928037 7103.4129134475 0.0) (10 3073.0476698981 7138.278569676 0.0) (10 3049.4860126894 7127.5525568674
0.0) (10 3036.6285561414 7082.4393529894 0.0) (10 3052.5872009599 7056.4291816043 0.0) (10 3035.4450226244
7043.7408371041 0.0))
((0 . "LWPOLYLINE") (100 . "AcDbEntity") (8 . "PLANTS") (62 . 94) (370 . 13) (100 . "AcDbPolyline") (90 . 2) (70 . 0)
(43 . 0.0) (10 3046.757239819 6764.7058823529) (10 3035.4450226244 6791.1007918552))
((0 . "LWPOLYLINE") (100 . "AcDbEntity") (8 . "PLANTS") (62 . 94) (370 . 13) (100 . "AcDbPolyline") (90 . 2) (70 . 0)
(43 . 0.0) (10 3046.757239819 6806.1842760181) (10 3035.4450226244 6791.1007918552))
((0 . "LWPOLYLINE") (100 . "AcDbEntity") (8 . "PLANTS") (62 . 94) (370 . 13) (100 . "AcDbPolyline") (90 . 2) (70 . 0)
(43 . 0.0) (10 3050.5278280543 316.742081448) (10 3035.4450226244 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3058.0694570136 354.4485294118 0.0) (10 3040.6865383503 355.315753117 0.0) (10 3028.8476157179
331.7184764692 0.0) (10 3035.4450226244 316.742081448 0.0))
((0 . "LWPOLYLINE") (100 . "AcDbEntity") (8 . "PLANTS") (62 . 94) (370 . 13) (100 . "AcDbPolyline") (90 . 2) (70 . 0)
(43 . 0.0) (10 3042.9864253394 6972.0962669683) (10 3039.2156108597 6994.7207013575))
((0 . "LWPOLYLINE") (100 . "AcDbEntity") (8 . "PLANTS") (62 . 94) (370 . 13) (100 . "AcDbPolyline") (90 . 3) (70 . 0)
(43 . 0.0) (10 3076.9230769231 7002.2624434389) (10 3054.2986425339 7002.1141402715) (10 3039.2156108597
6994.7207013575))
((0 . "LWPOLYLINE") (100 . "AcDbEntity") (8 . "PLANTS") (62 . 94) (370 . 13) (100 . "AcDbPolyline") (90 . 2) (70 . 0)
(43 . 0.0) (10 3039.2156108597 414.782239819) (10 3058.0694570136 403.4700226244))
((0 . "LWPOLYLINE") (100 . "AcDbEntity") (8 . "PLANTS") (62 . 94) (370 . 13) (100 . "AcDbPolyline") (90 . 3) (70 . 0)
(43 . 0.0) (10 3042.9864253394 6972.0962669683) (10 3058.0628959276 6964.4004524887) (10 3080.6938914027
6938.1596153846))
((0 . "LWPOLYLINE") (100 . "AcDbEntity") (8 . "PLANTS") (62 . 94) (370 . 13) (100 . "AcDbPolyline") (90 . 3) (70 . 0)
(43 . 0.0) (10 3046.757239819 6730.7692307692) (10 3042.9864253394 6745.8519230769) (10 3046.757239819 6764.7058823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3046.757239819 6764.7058823529 0.0) (10 3070.2961359414 6759.4620418393 0.0) (10 3082.9487082682
6788.1744535242 0.0) (10 3107.0889140271 6783.559841629 0.0))
((0 . "LWPOLYLINE") (100 . "AcDbEntity") (8 . "PLANTS") (62 . 94) (370 . 13) (100 . "AcDbPolyline") (90 . 3) (70 . 0)
(43 . 0.0) (10 3070.7830681092 6481.9453807876) (10 3125.942760181 6482.0485294118) (10 3141.0255656109
6485.6712669683))
((0 . "LWPOLYLINE") (100 . "AcDbEntity") (8 . "PLANTS") (62 . 94) (370 . 13) (100 . "AcDbPolyline") (90 . 2) (70 . 0)
(43 . 0.0) (10 3046.757239819 252.6385746606) (10 3054.2986425339 252.6385746606))
((0 . "LWPOLYLINE") (100 . "AcDbEntity") (8 . "PLANTS") (62 . 94) (370 . 13) (100 . "AcDbPolyline") (90 . 3) (70 . 0)
(43 . 0.0) (10 3061.8400452489 286.5752262443) (10 3055.4897058824 294.1245475113) (10 3050.5278280543 316.742081448))
((0 . "LWPOLYLINE") (100 . "AcDbEntity") (8 . "PLANTS") (62 . 94) (370 . 13) (100 . "AcDbPolyline") (90 . 3) (70 . 0)
(43 . 0.0) (10 3058.0694570136 354.4485294118) (10 3057.9213800905 335.596719457) (10 3050.5278280543 316.742081448))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3468151056) (40
. 1) (40 . 1) (40 . 1) (40 . 1) (10 3156.1085972851 248.8687782805 0.0) (10 3149.0815964064 236.2883465197 0.0) (10
3112.0795890009 228.9293397588 0.0) (10 3066.9677457012 226.9930119331 0.0) (10 3054.2986425339 252.6385746606 0.0))
((0 . "LWPOLYLINE") (100 . "AcDbEntity") (8 . "PLANTS") (62 . 94) (370 . 13) (100 . "AcDbPolyline") (90 . 3) (70 . 0)
(43 . 0.0) (10 3061.8400452489 286.5752262443) (10 3061.6852941176 267.7234162896) (10 3054.2986425339 252.6385746606))
((0 . "LWPOLYLINE") (100 . "AcDbEntity") (8 . "PLANTS") (62 . 94) (370 . 13) (100 . "AcDbPolyline") (90 . 2) (70 . 0)
(43 . 0.0) (10 3058.0694570136 354.4485294118) (10 3058.0694570136 403.4700226244))
((0 . "LWPOLYLINE") (100 . "AcDbEntity") (8 . "PLANTS") (62 . 94) (370 . 13) (100 . "AcDbPolyline") (90 . 3) (70 . 0)
(43 . 0.0) (10 3065.6108597285 426.0944570136) (10 3064.4132352941 411.0171945701) (10 3058.0694570136 403.4700226244))
((0 . "LWPOLYLINE") (100 . "AcDbEntity") (8 . "PLANTS") (62 . 94) (370 . 13) (100 . "AcDbPolyline") (90 . 3) (70 . 0)
(43 . 0.0) (10 3065.6108597285 426.0944570136) (10 3058.2242081448 441.1764705882) (10 3061.8400452489 456.2584841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3061.8400452488 286.5752262443 0.0) (10 3092.6062893026 288.7726697557 0.0) (10 3085.931831173
328.9227192474 0.0) (10 3107.0889140271 343.1363122172 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3065.6108597285 426.0944570136 0.0) (10 3089.0087322518 428.7706727908 0.0) (10 3090.3556261372
460.7779609277 0.0) (10 3114.6305429864 460.0311085973 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3092.0061085973 6938.1596153846 0.0) (10 3111.4212525331 6957.7978019468 0.0) (10 3087.5007118396
6987.0801685592 0.0) (10 3076.9230769231 7002.2624434389 0.0))
((0 . "LWPOLYLINE") (100 . "AcDbEntity") (8 . "PLANTS") (62 . 94) (370 . 13) (100 . "AcDbPolyline") (90 . 2) (70 . 0)
(43 . 0.0) (10 3092.0061085973 6938.1596153846) (10 3080.6938914027 6938.1596153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3137.2549773756 6685.520361991 0.0) (10 3132.6004508408 6658.6553053282 0.0) (10 3096.7478537522
6648.3938064271 0.0) (10 3080.6938914027 6674.2081447964 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3080.6938914027 6564.8564479638 0.0) (10 3100.1456520532 6577.8707810621 0.0) (10 3104.3047326023
6613.7058146942 0.0) (10 3080.6938914027 6625.188800905 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4678968573) (40
. 1) (40 . 1) (40 . 1) (40 . 1) (10 3265.4599547512 452.4886877828 0.0) (10 3266.5915811425 500.4221681031 0.0) (10
3212.446403787 587.2819715656 0.0) (10 3130.0754016312 653.0315023375 0.0) (10 3080.6938914028 667.4208144798 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5375443178) (40
. 1) (40 . 1) (40 . 1) (40 . 1) (10 3080.6938914025 667.4208144796 0.0) (10 3089.0147232254 622.4374210564 0.0) (10
3156.0172730612 566.6905290661 0.0) (10 3214.2335545437 504.5481726968 0.0) (10 3220.2110859728 463.8009049773 0.0))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.4056236168)
(40 . 0.7856682462) (40 . 0.8603106417) (40 . 1) (40 . 1) (40 . 1) (40 . 1) (10 3112.7450226244 507.1634615385 0.0) (10
3121.3881742315 544.1694148863 0.0) (10 3068.9353345616 588.6734494626 0.0) (10 3025.695800341 659.893437023 0.0) (10
3043.084663557 700.962246273 0.0) (10 3123.2239824566 627.1315275933 0.0) (10 3080.6938914027 667.4208144796 0.0))
((0 . "LWPOLYLINE") (100 . "AcDbEntity") (8 . "PLANTS") (62 . 94) (370 . 13) (100 . "AcDbPolyline") (90 . 2) (70 . 0)
(43 . 0.0) (10 3112.7450226244 507.1634615385) (10 3084.464479638 524.1317873303))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3092.0061085973 6938.1596153846 0.0) (10 3114.179590236 6914.5501593877 0.0) (10 3149.3273396452
6911.2396622908 0.0) (10 3178.7330316742 6919.3064479638 0.0))
((0 . "LWPOLYLINE") (100 . "AcDbEntity") (8 . "PLANTS") (62 . 94) (370 . 13) (100 . "AcDbPolyline") (90 . 2) (70 . 0)
(43 . 0.0) (10 3142.7014831574 720.211199095) (10 3099.5475113122 720.211199095))
((0 . "LWPOLYLINE") (100 . "AcDbEntity") (8 . "PLANTS") (62 . 94) (370 . 13) (100 . "AcDbPolyline") (90 . 2) (70 . 0)
(43 . 0.0) (10 3163.65 6783.559841629) (10 3107.0889140271 6783.559841629))
((0 . "LWPOLYLINE") (100 . "AcDbEntity") (8 . "PLANTS") (62 . 94) (370 . 13) (100 . "AcDbPolyline") (90 . 2) (70 . 0)
(43 . 0.0) (10 3110.8597285068 6738.3109728507) (10 3107.0889140271 6783.559841629))
((0 . "LWPOLYLINE") (100 . "AcDbEntity") (8 . "PLANTS") (62 . 94) (370 . 13) (100 . "AcDbPolyline") (90 . 3) (70 . 0)
(43 . 0.0) (10 3137.2549773756 6843.8914027149) (10 3117.5062217195 6821.2669683258) (10 3107.0889140271
6783.559841629))
((0 . "LWPOLYLINE") (100 . "AcDbEntity") (8 . "PLANTS") (62 . 94) (370 . 13) (100 . "AcDbPolyline") (90 . 2) (70 . 0)
(43 . 0.0) (10 3122.1719457014 343.1363122172) (10 3107.0889140271 343.1363122172))
((0 . "LWPOLYLINE") (100 . "AcDbEntity") (8 . "PLANTS") (62 . 94) (370 . 13) (100 . "AcDbPolyline") (90 . 3) (70 . 0)
(43 . 0.0) (10 3137.2549773756 422.3218325792) (10 3115.6804298643 395.92760181) (10 3107.0889140271 343.1363122172))
((0 . "LWPOLYLINE") (100 . "AcDbEntity") (8 . "PLANTS") (62 . 94) (370 . 13) (100 . "AcDbPolyline") (90 . 3) (70 . 0)
(43 . 0.0) (10 3129.7133484163 6726.9987556561) (10 3118.4076923077 6737.1066742081) (10 3110.8597285068
6738.3109728507))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3129.7133484163 6708.1447963801 0.0) (10 3101.2411929865 6682.9354006047 0.0) (10 3074.8433283396
6743.7098662163 0.0) (10 3110.8597285068 6738.3109728507 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3112.7450226244 507.1634615385 0.0) (10 3153.0065769341 501.3173590171 0.0) (10 3175.16688169
458.7787681727 0.0) (10 3215.686199095 454.7512443439 0.0))
((0 . "LWPOLYLINE") (100 . "AcDbEntity") (8 . "PLANTS") (62 . 94) (370 . 13) (100 . "AcDbPolyline") (90 . 2) (70 . 0)
(43 . 0.0) (10 3112.7450226244 507.1634615385) (10 3114.6305429864 460.0311085973))
((0 . "LWPOLYLINE") (100 . "AcDbEntity") (8 . "PLANTS") (62 . 94) (370 . 13) (100 . "AcDbPolyline") (90 . 3) (70 . 0)
(43 . 0.0) (10 3137.2549773756 422.3218325792) (10 3128.6634615385 444.9462669683) (10 3114.6305429864 460.0311085973))
((0 . "LWPOLYLINE") (100 . "AcDbEntity") (8 . "PLANTS") (62 . 94) (370 . 13) (100 . "AcDbPolyline") (90 . 3) (70 . 0)
(43 . 0.0) (10 3122.1719457014 343.1363122172) (10 3126.9992081448 312.9722850679) (10 3137.2549773756 297.8874434389))
((0 . "LWPOLYLINE") (100 . "AcDbEntity") (8 . "PLANTS") (62 . 94) (370 . 13) (100 . "AcDbPolyline") (90 . 2) (70 . 0)
(43 . 0.0) (10 3148.5671945701 346.9089366516) (10 3122.1719457014 343.1363122172))
((0 . "LWPOLYLINE") (100 . "AcDbEntity") (8 . "PLANTS") (62 . 94) (370 . 13) (100 . "AcDbPolyline") (90 . 2) (70 . 0)
(43 . 0.0) (10 3129.7133484163 6726.9987556561) (10 3129.7133484163 6708.1447963801))
((0 . "LWPOLYLINE") (100 . "AcDbEntity") (8 . "PLANTS") (62 . 94) (370 . 13) (100 . "AcDbPolyline") (90 . 3) (70 . 0)
(43 . 0.0) (10 3129.7133484163 6726.9987556561) (10 3148.5671945701 6731.9735294118) (10 3167.4208144796
6745.8519230769))
((0 . "LWPOLYLINE") (100 . "AcDbEntity") (8 . "PLANTS") (62 . 94) (370 . 13) (100 . "AcDbPolyline") (90 . 3) (70 . 0)
(43 . 0.0) (10 3137.2549773756 6685.520361991) (10 3136.0574660633 6700.5964932127) (10 3129.7133484163
6708.1447963801))
((0 . "LWPOLYLINE") (100 . "AcDbEntity") (8 . "PLANTS") (62 . 94) (370 . 13) (100 . "AcDbPolyline") (90 . 2) (70 . 0)
(43 . 0.0) (10 3141.0255656109 6451.7346153846) (10 3133.4841628959 6444.1929864253))
((0 . "LWPOLYLINE") (100 . "AcDbEntity") (8 . "PLANTS") (62 . 94) (370 . 13) (100 . "AcDbPolyline") (90 . 2) (70 . 0)
(43 . 0.0) (10 3137.2549773756 6843.8914027149) (10 3156.1085972851 6843.8914027149))
((0 . "LWPOLYLINE") (100 . "AcDbEntity") (8 . "PLANTS") (62 . 94) (370 . 13) (100 . "AcDbPolyline") (90 . 3) (70 . 0)
(43 . 0.0) (10 3174.9622171946 6683.6347285068) (10 3148.5671945701 6681.8977375566) (10 3137.2549773756
6685.520361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3137.2549773756 6610.1053167421 0.0) (10 3121.8587635035 6588.8341623253 0.0) (10 3150.3353738139
6567.0630467818 0.0) (10 3171.1916289593 6579.9399321267 0.0))
((0 . "LWPOLYLINE") (100 . "AcDbEntity") (8 . "PLANTS") (62 . 94) (370 . 13) (100 . "AcDbPolyline") (90 . 3) (70 . 0)
(43 . 0.0) (10 3137.2549773756 422.3218325792) (10 3152.3312217195 414.7746606335) (10 3174.9622171946 384.6153846154))
((0 . "LWPOLYLINE") (100 . "AcDbEntity") (8 . "PLANTS") (62 . 94) (370 . 13) (100 . "AcDbPolyline") (90 . 3) (70 . 0)
(43 . 0.0) (10 3156.1085972851 248.8687782805) (10 3142.2234162896 267.7234162896) (10 3137.2549773756 297.8874434389))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3148.5671945701 346.9089366516 0.0) (10 3145.4208688483 337.8476033929 0.0) (10 3156.5575065733
303.4075532812 0.0) (10 3137.2549773756 297.8874434389 0.0))
((0 . "LWPOLYLINE") (100 . "AcDbEntity") (8 . "PLANTS") (62 . 94) (370 . 13) (100 . "AcDbPolyline") (90 . 2) (70 . 0)
(43 . 0.0) (10 3144.7963800905 6527.149321267) (10 3141.0255656109 6534.6910633484))
((0 . "LWPOLYLINE") (100 . "AcDbEntity") (8 . "PLANTS") (62 . 94) (370 . 13) (100 . "AcDbPolyline") (90 . 2) (70 . 0)
(43 . 0.0) (10 3141.0255656109 6485.6712669683) (10 3174.9622171946 6478.129638009))
((0 . "LWPOLYLINE") (100 . "AcDbEntity") (8 . "PLANTS") (62 . 94) (370 . 13) (100 . "AcDbPolyline") (90 . 2) (70 . 0)
(43 . 0.0) (10 3144.7963800905 6527.149321267) (10 3141.0255656109 6485.6712669683))
((0 . "LWPOLYLINE") (100 . "AcDbEntity") (8 . "PLANTS") (62 . 94) (370 . 13) (100 . "AcDbPolyline") (90 . 2) (70 . 0)
(43 . 0.0) (10 3144.7963800905 6527.149321267) (10 3159.8794117647 6527.149321267))
((0 . "LWPOLYLINE") (100 . "AcDbEntity") (8 . "PLANTS") (62 . 94) (370 . 13) (100 . "AcDbPolyline") (90 . 2) (70 . 0)
(43 . 0.0) (10 3144.7963800905 6353.6952488688) (10 3159.8794117647 6353.6952488688))
((0 . "LWPOLYLINE") (100 . "AcDbEntity") (8 . "PLANTS") (62 . 94) (370 . 13) (100 . "AcDbPolyline") (90 . 2) (70 . 0)
(43 . 0.0) (10 3148.5671945701 346.9089366516) (10 3174.9622171946 384.6153846154))
((0 . "LWPOLYLINE") (100 . "AcDbEntity") (8 . "PLANTS") (62 . 94) (370 . 13) (100 . "AcDbPolyline") (90 . 3) (70 . 0)
(43 . 0.0) (10 3167.4208144796 6798.6425339367) (10 3160.935520362 6809.9547511312) (10 3156.1085972851
6843.8914027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3156.1085972851 6843.8914027149 0.0) (10 3175.1469250237 6858.3160255597 0.0) (10 3163.4652132072
6886.0280601995 0.0) (10 3182.5038461538 6900.4524886878 0.0))
((0 . "LWPOLYLINE") (100 . "AcDbEntity") (8 . "PLANTS") (62 . 94) (370 . 13) (100 . "AcDbPolyline") (90 . 2) (70 . 0)
(43 . 0.0) (10 3156.1085972851 248.8687782805) (10 3190.0452488688 252.6385746606))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4093685658) (40
. 1) (40 . 1) (40 . 1) (40 . 1) (10 3159.8794117646 6527.149321267 0.0) (10 3173.5857378627 6513.6929146336 0.0) (10
3217.4736020459 6522.4095496878 0.0) (10 3203.8984327319 6575.5975134019 0.0) (10 3171.1916289592 6572.3981900453 0.0))
((0 . "LWPOLYLINE") (100 . "AcDbEntity") (8 . "PLANTS") (62 . 94) (370 . 13) (100 . "AcDbPolyline") (90 . 3) (70 . 0)
(43 . 0.0) (10 3159.8794117647 6527.149321267) (10 3170.1418552036 6553.5442307692) (10 3171.1916289593
6572.3981900452))
((0 . "LWPOLYLINE") (100 . "AcDbEntity") (8 . "PLANTS") (62 . 94) (370 . 13) (100 . "AcDbPolyline") (90 . 2) (70 . 0)
(43 . 0.0) (10 3159.8794117647 6353.6952488688) (10 3171.1916289593 6342.3830316742))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3884884295) (40
. 1) (40 . 1) (40 . 1) (40 . 1) (10 3205.128280543 6357.4660633483 0.0) (10 3213.0655869473 6371.9799592868 0.0) (10
3197.2121331254 6406.3909710754 0.0) (10 3158.1916596721 6375.8552669979 0.0) (10 3159.8794117647 6353.6952488687 0.0))
((0 . "LWPOLYLINE") (100 . "AcDbEntity") (8 . "PLANTS") (62 . 94) (370 . 13) (100 . "AcDbPolyline") (90 . 3) (70 . 0)
(43 . 0.0) (10 3171.1916289593 6319.7585972851) (10 3160.9292986425 6297.1341628959) (10 3159.8794117647
6282.0513574661))
((0 . "LWPOLYLINE") (100 . "AcDbEntity") (8 . "PLANTS") (62 . 94) (370 . 13) (100 . "AcDbPolyline") (90 . 2) (70 . 0)
(43 . 0.0) (10 3167.4208144796 6768.4763574661) (10 3163.65 6783.559841629))
((0 . "LWPOLYLINE") (100 . "AcDbEntity") (8 . "PLANTS") (62 . 94) (370 . 13) (100 . "AcDbPolyline") (90 . 2) (70 . 0)
(43 . 0.0) (10 3167.4208144796 6798.6425339367) (10 3163.65 6783.559841629))
((0 . "LWPOLYLINE") (100 . "AcDbEntity") (8 . "PLANTS") (62 . 94) (370 . 13) (100 . "AcDbPolyline") (90 . 2) (70 . 0)
(43 . 0.0) (10 3167.4208144796 6798.6425339367) (10 3210.7843891403 6817.4964932127))
((0 . "LWPOLYLINE") (100 . "AcDbEntity") (8 . "PLANTS") (62 . 94) (370 . 13) (100 . "AcDbPolyline") (90 . 2) (70 . 0)
(43 . 0.0) (10 3167.4208144796 6768.4763574661) (10 3167.4208144796 6745.8519230769))
((0 . "LWPOLYLINE") (100 . "AcDbEntity") (8 . "PLANTS") (62 . 94) (370 . 13) (100 . "AcDbPolyline") (90 . 2) (70 . 0)
(43 . 0.0) (10 3167.4208144796 6768.4763574661) (10 3208.8988687783 6776.0180995475))
((0 . "LWPOLYLINE") (100 . "AcDbEntity") (8 . "PLANTS") (62 . 94) (370 . 13) (100 . "AcDbPolyline") (90 . 2) (70 . 0)
(43 . 0.0) (10 3171.1916289593 6734.5397058824) (10 3167.4208144796 6745.8519230769))
((0 . "LWPOLYLINE") (100 . "AcDbEntity") (8 . "PLANTS") (62 . 94) (370 . 13) (100 . "AcDbPolyline") (90 . 2) (70 . 0)
(43 . 0.0) (10 3167.4208144796 6426.5962669683) (10 3174.9622171946 6451.7346153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3171.1916289593 6734.5397058824 0.0) (10 3192.7816419646 6733.510781359 0.0) (10 3217.8115617622
6726.0540772944 0.0) (10 3227.7527149321 6704.374321267 0.0))
((0 . "LWPOLYLINE") (100 . "AcDbEntity") (8 . "PLANTS") (62 . 94) (370 . 13) (100 . "AcDbPolyline") (90 . 3) (70 . 0)
(43 . 0.0) (10 3171.1916289593 6734.5397058824) (10 3171.3398190045 6692.9944570136) (10 3174.9622171946
6683.6347285068))
((0 . "LWPOLYLINE") (100 . "AcDbEntity") (8 . "PLANTS") (62 . 94) (370 . 13) (100 . "AcDbPolyline") (90 . 2) (70 . 0)
(43 . 0.0) (10 3171.1916289593 6572.3981900452) (10 3171.1916289593 6579.9399321267))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3174.9622171946 6683.6347285068 0.0) (10 3185.7122600958 6645.2373184572 0.0) (10 3129.9751704834
6619.7071938945 0.0) (10 3171.1916289593 6579.9399321267 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3174.9622171946 6683.6347285068 0.0) (10 3191.4470368287 6697.2076230739 0.0) (10 3217.9273859105
6678.8427409509 0.0) (10 3227.7527149321 6704.374321267 0.0))
((0 . "LWPOLYLINE") (100 . "AcDbEntity") (8 . "PLANTS") (62 . 94) (370 . 13) (100 . "AcDbPolyline") (90 . 2) (70 . 0)
(43 . 0.0) (10 3174.9622171946 6478.129638009) (10 3174.9622171946 6451.7346153846))
((0 . "LWPOLYLINE") (100 . "AcDbEntity") (8 . "PLANTS") (62 . 94) (370 . 13) (100 . "AcDbPolyline") (90 . 3) (70 . 0)
(43 . 0.0) (10 3174.9622171946 6478.129638009) (10 3197.5866515837 6484.4737556561) (10 3264.1446034594
6482.7914664458))
((0 . "LWPOLYLINE") (100 . "AcDbEntity") (8 . "PLANTS") (62 . 94) (370 . 13) (100 . "AcDbPolyline") (90 . 2) (70 . 0)
(43 . 0.0) (10 3186.2744343891 6447.963800905) (10 3174.9622171946 6451.7346153846))
((0 . "LWPOLYLINE") (100 . "AcDbEntity") (8 . "PLANTS") (62 . 94) (370 . 13) (100 . "AcDbPolyline") (90 . 2) (70 . 0)
(43 . 0.0) (10 3174.9622171946 6229.2608597285) (10 3174.9622171946 6251.8852941176))
((0 . "LWPOLYLINE") (100 . "AcDbEntity") (8 . "PLANTS") (62 . 94) (370 . 13) (100 . "AcDbPolyline") (90 . 2) (70 . 0)
(43 . 0.0) (10 3201.3574660633 377.0729638009) (10 3174.9622171946 384.6153846154))
((0 . "LWPOLYLINE") (100 . "AcDbEntity") (8 . "PLANTS") (62 . 94) (370 . 13) (100 . "AcDbPolyline") (90 . 2) (70 . 0)
(43 . 0.0) (10 3178.7330316742 6930.6186651584) (10 3178.7330316742 6919.3064479638))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3597306304)
(40 . 0.6204777805) (40 . 1) (40 . 1) (40 . 1) (40 . 1) (10 3178.7330316742 6930.6186651584 0.0) (10 3153.2541186974
6946.4391064485 0.0) (10 3135.0218352796 6992.1048669738 0.0) (10 3107.9741375603 7077.7395842373 0.0) (10
3188.985463253 7103.2507143134 0.0) (10 3190.0452488688 7055.0530542986 0.0))
((0 . "LWPOLYLINE") (100 . "AcDbEntity") (8 . "PLANTS") (62 . 94) (370 . 13) (100 . "AcDbPolyline") (90 . 2) (70 . 0)
(43 . 0.0) (10 3178.7330316742 6930.6186651584) (10 3190.0452488688 6945.7013574661))
((0 . "LWPOLYLINE") (100 . "AcDbEntity") (8 . "PLANTS") (62 . 94) (370 . 13) (100 . "AcDbPolyline") (90 . 2) (70 . 0)
(43 . 0.0) (10 3182.5038461538 6900.4524886878) (10 3178.7330316742 6919.3064479638))
((0 . "LWPOLYLINE") (100 . "AcDbEntity") (8 . "PLANTS") (62 . 94) (370 . 13) (100 . "AcDbPolyline") (90 . 2) (70 . 0)
(43 . 0.0) (10 3197.5866515837 6896.6820135747) (10 3182.5038461538 6900.4524886878))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.540513322)
(40 . 0.9149692601) (40 . 1) (40 . 1) (40 . 1) (40 . 1) (10 3272.4340467988 7097.4553063224 0.0) (10 3239.3620420766
7083.7020782253 0.0) (10 3225.6109690904 7027.1122259259 0.0) (10 3197.6697313368 6976.8686667889 0.0) (10
3189.1931191332 6951.0498513294 0.0) (10 3190.0452488687 6945.7013574661 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3254.1477375566 6983.4084841629 0.0) (10 3224.4210006208 6980.0296491964 0.0) (10 3230.8720788367
6923.8645364104 0.0) (10 3190.0452488688 6945.7013574661 0.0))
((0 . "LWPOLYLINE") (100 . "AcDbEntity") (8 . "PLANTS") (62 . 94) (370 . 13) (100 . "AcDbPolyline") (90 . 2) (70 . 0)
(43 . 0.0) (10 3190.0452488688 252.6385746606) (10 3190.0452488688 267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3201.3574660634 369.5333710407 0.0) (10 3190.0548308906 354.6956814325 0.0) (10 3143.6629825737
283.5555245672 0.0) (10 3190.0452488688 267.7234162896 0.0))
((0 . "LWPOLYLINE") (100 . "AcDbEntity") (8 . "PLANTS") (62 . 94) (370 . 13) (100 . "AcDbPolyline") (90 . 2) (70 . 0)
(43 . 0.0) (10 3208.8988687783 279.0356334842) (10 3190.0452488688 267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3190.0452488688 252.6385746606 0.0) (10 3197.1212485326 216.6180346249 0.0) (10 3234.0620776289
242.7372134705 0.0) (10 3254.1477375566 233.7858597285 0.0))
((0 . "LWPOLYLINE") (100 . "AcDbEntity") (8 . "PLANTS") (62 . 94) (370 . 13) (100 . "AcDbPolyline") (90 . 3) (70 . 0)
(43 . 0.0) (10 3216.4404977376 6851.4331447964) (10 3207.8424208145 6881.5985294118) (10 3197.5866515837
6896.6820135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3197.5866515837 6896.6820135747 0.0) (10 3233.3226405932 6921.4838992643 0.0) (10 3276.4429222893
6864.4706311961 0.0) (10 3314.4796380091 6896.6820135748 0.0))
((0 . "LWPOLYLINE") (100 . "AcDbEntity") (8 . "PLANTS") (62 . 94) (370 . 13) (100 . "AcDbPolyline") (90 . 2) (70 . 0)
(43 . 0.0) (10 3201.3574660633 377.0729638009) (10 3201.3574660633 369.5333710407))
((0 . "LWPOLYLINE") (100 . "AcDbEntity") (8 . "PLANTS") (62 . 94) (370 . 13) (100 . "AcDbPolyline") (90 . 3) (70 . 0)
(43 . 0.0) (10 3201.3574660633 377.0729638009) (10 3206.3324660633 399.6925339367) (10 3216.4404977376 407.2398190045))
((0 . "LWPOLYLINE") (100 . "AcDbEntity") (8 . "PLANTS") (62 . 94) (370 . 13) (100 . "AcDbPolyline") (90 . 2) (70 . 0)
(43 . 0.0) (10 3201.3574660633 369.5333710407) (10 3235.2941176471 369.5333710407))
((0 . "LWPOLYLINE") (100 . "AcDbEntity") (8 . "PLANTS") (62 . 94) (370 . 13) (100 . "AcDbPolyline") (90 . 2) (70 . 0)
(43 . 0.0) (10 3208.8988687783 6776.0180995475) (10 3242.835520362 6776.0180995475))
((0 . "LWPOLYLINE") (100 . "AcDbEntity") (8 . "PLANTS") (62 . 94) (370 . 13) (100 . "AcDbPolyline") (90 . 2) (70 . 0)
(43 . 0.0) (10 3208.8988687783 6776.0180995475) (10 3210.7843891403 6817.4964932127))
((0 . "LWPOLYLINE") (100 . "AcDbEntity") (8 . "PLANTS") (62 . 94) (370 . 13) (100 . "AcDbPolyline") (90 . 2) (70 . 0)
(43 . 0.0) (10 3208.8988687783 6632.7297511312) (10 3246.6063348416 6625.188800905))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3208.8988687783 279.0356334842 0.0) (10 3234.4355265203 285.4628006048 0.0) (10 3268.4124935813
264.1908711626 0.0) (10 3254.1477375566 233.7858597285 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3208.8988687783 279.0356334842 0.0) (10 3204.7161197749 304.2545323231 0.0) (10 3225.2858451371
324.1127592934 0.0) (10 3246.6063348416 331.8240950226 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3242.835520362 6776.0180995475 0.0) (10 3254.348297233 6798.4546411875 0.0) (10 3234.1118054491
6824.0508559075 0.0) (10 3210.7843891403 6817.4964932127 0.0))
((0 . "LWPOLYLINE") (100 . "AcDbEntity") (8 . "PLANTS") (62 . 94) (370 . 13) (100 . "AcDbPolyline") (90 . 2) (70 . 0)
(43 . 0.0) (10 3216.4404977376 6851.4331447964) (10 3210.7843891403 6817.4964932127))
((0 . "LWPOLYLINE") (100 . "AcDbEntity") (8 . "PLANTS") (62 . 94) (370 . 13) (100 . "AcDbPolyline") (90 . 2) (70 . 0)
(43 . 0.0) (10 3246.6063348416 452.4886877828) (10 3215.686199095 454.7512443439))
((0 . "LWPOLYLINE") (100 . "AcDbEntity") (8 . "PLANTS") (62 . 94) (370 . 13) (100 . "AcDbPolyline") (90 . 2) (70 . 0)
(43 . 0.0) (10 3215.686199095 454.7512443439) (10 3216.4404977376 407.2398190045))
((0 . "LWPOLYLINE") (100 . "AcDbEntity") (8 . "PLANTS") (62 . 94) (370 . 13) (100 . "AcDbPolyline") (90 . 3) (70 . 0)
(43 . 0.0) (10 3215.686199095 454.7512443439) (10 3212.6696832579 460.0311085973) (10 3220.2110859729 463.8009049774))
((0 . "LWPOLYLINE") (100 . "AcDbEntity") (8 . "PLANTS") (62 . 94) (370 . 13) (100 . "AcDbPolyline") (90 . 2) (70 . 0)
(43 . 0.0) (10 3215.686199095 454.7512443439) (10 3220.2110859729 463.8009049774))
((0 . "LWPOLYLINE") (100 . "AcDbEntity") (8 . "PLANTS") (62 . 94) (370 . 13) (100 . "AcDbPolyline") (90 . 3) (70 . 0)
(43 . 0.0) (10 3216.4404977376 6851.4331447964) (10 3242.835520362 6855.0553167421) (10 3280.5429864253
6840.1209276018))
((0 . "LWPOLYLINE") (100 . "AcDbEntity") (8 . "PLANTS") (62 . 94) (370 . 13) (100 . "AcDbPolyline") (90 . 3) (70 . 0)
(43 . 0.0) (10 3246.6063348416 388.3851809955) (10 3239.0583710407 398.5002262443) (10 3216.4404977376 407.2398190045))
((0 . "LWPOLYLINE") (100 . "AcDbEntity") (8 . "PLANTS") (62 . 94) (370 . 13) (100 . "AcDbPolyline") (90 . 2) (70 . 0)
(43 . 0.0) (10 3239.0649321267 6704.374321267) (10 3227.7527149321 6704.374321267))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4288307575)
(40 . 0.8042129021) (40 . 1) (40 . 1) (40 . 1) (40 . 1) (10 3318.2504524887 493.9677601809 0.0) (10 3373.1715759458
530.6521232889 0.0) (10 3347.9242283709 653.3935462583 0.0) (10 3307.2922621401 770.668422311 0.0) (10 3268.4784715233
846.7109999152 0.0) (10 3246.9053127511 858.7217705678 0.0))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.1018088138)
(40 . 0.1846276668) (40 . 0.5072516955) (40 . 1) (40 . 1) (40 . 1) (40 . 1) (10 3291.8552036198 565.6108597284 0.0) (10
3286.325656172 570.7878461494 0.0) (10 3282.515587028 585.8593599684 0.0) (10 3264.6620496278 626.4855314963 0.0) (10
3282.3152321608 709.0159527781 0.0) (10 3210.2159872823 762.2743233014 0.0) (10 3236.0183721646 812.996620105 0.0))
((0 . "LWPOLYLINE") (100 . "AcDbEntity") (8 . "PLANTS") (62 . 94) (370 . 13) (100 . "AcDbPolyline") (90 . 2) (70 . 0)
(43 . 0.0) (10 3235.2941176471 369.5333710407) (10 3246.6063348416 331.8240950226))
((0 . "LWPOLYLINE") (100 . "AcDbEntity") (8 . "PLANTS") (62 . 94) (370 . 13) (100 . "AcDbPolyline") (90 . 2) (70 . 0)
(43 . 0.0) (10 3246.6063348416 388.3851809955) (10 3235.2941176471 369.5333710407))
((0 . "LWPOLYLINE") (100 . "AcDbEntity") (8 . "PLANTS") (62 . 94) (370 . 13) (100 . "AcDbPolyline") (90 . 2) (70 . 0)
(43 . 0.0) (10 3239.0649321267 6930.6186651584) (10 3284.313800905 6934.3891402715))
((0 . "LWPOLYLINE") (100 . "AcDbEntity") (8 . "PLANTS") (62 . 94) (370 . 13) (100 . "AcDbPolyline") (90 . 3) (70 . 0)
(43 . 0.0) (10 3239.0649321267 6704.374321267) (10 3249.179638009 6685.520361991) (10 3254.1477375566 6655.3541855204))
((0 . "LWPOLYLINE") (100 . "AcDbEntity") (8 . "PLANTS") (62 . 94) (370 . 13) (100 . "AcDbPolyline") (90 . 3) (70 . 0)
(43 . 0.0) (10 3257.9185520362 6742.0814479638) (10 3252.9435520362 6715.8340497738) (10 3239.0649321267
6704.374321267))
((0 . "LWPOLYLINE") (100 . "AcDbEntity") (8 . "PLANTS") (62 . 94) (370 . 13) (100 . "AcDbPolyline") (90 . 2) (70 . 0)
(43 . 0.0) (10 3242.835520362 6776.0180995475) (10 3254.1477375566 6768.4763574661))
((0 . "LWPOLYLINE") (100 . "AcDbEntity") (8 . "PLANTS") (62 . 94) (370 . 13) (100 . "AcDbPolyline") (90 . 2) (70 . 0)
(43 . 0.0) (10 3250.3771493213 6617.6470588235) (10 3246.6063348416 6625.188800905))
((0 . "LWPOLYLINE") (100 . "AcDbEntity") (8 . "PLANTS") (62 . 94) (370 . 13) (100 . "AcDbPolyline") (90 . 3) (70 . 0)
(43 . 0.0) (10 3246.6063348416 6625.188800905) (10 3253.0978506787 6640.2714932127) (10 3254.1477375566
6655.3541855204))
((0 . "LWPOLYLINE") (100 . "AcDbEntity") (8 . "PLANTS") (62 . 94) (370 . 13) (100 . "AcDbPolyline") (90 . 2) (70 . 0)
(43 . 0.0) (10 3246.6063348416 452.4886877828) (10 3265.4599547511 452.4886877828))
((0 . "LWPOLYLINE") (100 . "AcDbEntity") (8 . "PLANTS") (62 . 94) (370 . 13) (100 . "AcDbPolyline") (90 . 2) (70 . 0)
(43 . 0.0) (10 3246.6063348416 452.4886877828) (10 3261.6893665158 395.92760181))
((0 . "LWPOLYLINE") (100 . "AcDbEntity") (8 . "PLANTS") (62 . 94) (370 . 13) (100 . "AcDbPolyline") (90 . 2) (70 . 0)
(43 . 0.0) (10 3246.6063348416 388.3851809955) (10 3254.1477375566 388.3851809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3310.7088235294 275.2630090498 0.0) (10 3275.7392673592 276.4267549593 0.0) (10 3279.3068571662
328.1045742585 0.0) (10 3246.6063348416 331.8240950227 0.0))
((0 . "LWPOLYLINE") (100 . "AcDbEntity") (8 . "PLANTS") (62 . 94) (370 . 13) (100 . "AcDbPolyline") (90 . 3) (70 . 0)
(43 . 0.0) (10 3250.3771493213 6617.6470588235) (10 3269.2307692308 6612.8201357466) (10 3276.9072761559
6608.2910812945))
((0 . "LWPOLYLINE") (100 . "AcDbEntity") (8 . "PLANTS") (62 . 94) (370 . 13) (100 . "AcDbPolyline") (90 . 3) (70 . 0)
(43 . 0.0) (10 3265.4599547511 6576.1686651584) (10 3255.3518099548 6587.4812217195) (10 3250.3771493213
6617.6470588235))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3254.1477375566 6983.4084841629 0.0) (10 3250.1872875348 7018.8059604517 0.0) (10 3292.6333065006
7042.6542689567 0.0) (10 3303.1674208145 7070.1357466063 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4946055773) (40
. 1) (40 . 1) (40 . 1) (40 . 1) (10 3254.1477375566 6983.4084841629 0.0) (10 3273.761246807 6979.154447205 0.0) (10
3301.304782989 7008.2388672316 0.0) (10 3340.1724351902 7001.5128572174 0.0) (10 3355.9576923077 7013.5746606335 0.0))
((0 . "LWPOLYLINE") (100 . "AcDbEntity") (8 . "PLANTS") (62 . 94) (370 . 13) (100 . "AcDbPolyline") (90 . 2) (70 . 0)
(43 . 0.0) (10 3261.6893665158 6768.4763574661) (10 3254.1477375566 6768.4763574661))
((0 . "LWPOLYLINE") (100 . "AcDbEntity") (8 . "PLANTS") (62 . 94) (370 . 13) (100 . "AcDbPolyline") (90 . 3) (70 . 0)
(43 . 0.0) (10 3257.9185520362 6742.0814479638) (10 3250.5319004525 6749.6297511312) (10 3254.1477375566
6768.4763574661))
((0 . "LWPOLYLINE") (100 . "AcDbEntity") (8 . "PLANTS") (62 . 94) (370 . 13) (100 . "AcDbPolyline") (90 . 3) (70 . 0)
(43 . 0.0) (10 3281.2480917269 6650.9757677426) (10 3276.7721719457 6654.1566742081) (10 3254.1477375566
6655.3541855204))
((0 . "LWPOLYLINE") (100 . "AcDbEntity") (8 . "PLANTS") (62 . 94) (370 . 13) (100 . "AcDbPolyline") (90 . 3) (70 . 0)
(43 . 0.0) (10 3288.0843891403 369.5333710407) (10 3269.2373303167 370.7367647059) (10 3254.1477375566 388.3851809955))
((0 . "LWPOLYLINE") (100 . "AcDbEntity") (8 . "PLANTS") (62 . 94) (370 . 13) (100 . "AcDbPolyline") (90 . 2) (70 . 0)
(43 . 0.0) (10 3261.6893665158 395.92760181) (10 3254.1477375566 388.3851809955))
((0 . "LWPOLYLINE") (100 . "AcDbEntity") (8 . "PLANTS") (62 . 94) (370 . 13) (100 . "AcDbPolyline") (90 . 3) (70 . 0)
(43 . 0.0) (10 3314.4796380091 248.8687782805) (10 3291.8552036199 233.7858597285) (10 3254.1477375566 233.7858597285))
((0 . "LWPOLYLINE") (100 . "AcDbEntity") (8 . "PLANTS") (62 . 94) (370 . 13) (100 . "AcDbPolyline") (90 . 2) (70 . 0)
(43 . 0.0) (10 3257.9185520362 6742.0814479638) (10 3269.2307692308 6749.6231900452))
((0 . "LWPOLYLINE") (100 . "AcDbEntity") (8 . "PLANTS") (62 . 94) (370 . 13) (100 . "AcDbPolyline") (90 . 2) (70 . 0)
(43 . 0.0) (10 3269.2307692308 6749.6231900452) (10 3261.6893665158 6768.4763574661))
((0 . "LWPOLYLINE") (100 . "AcDbEntity") (8 . "PLANTS") (62 . 94) (370 . 13) (100 . "AcDbPolyline") (90 . 2) (70 . 0)
(43 . 0.0) (10 3286.1990950226 6772.2476244344) (10 3261.6893665158 6768.4763574661))
((0 . "LWPOLYLINE") (100 . "AcDbEntity") (8 . "PLANTS") (62 . 94) (370 . 13) (100 . "AcDbPolyline") (90 . 2) (70 . 0)
(43 . 0.0) (10 3288.0843891403 395.92760181) (10 3261.6893665158 395.92760181))
((0 . "LWPOLYLINE") (100 . "AcDbEntity") (8 . "PLANTS") (62 . 94) (370 . 13) (100 . "AcDbPolyline") (90 . 3) (70 . 0)
(43 . 0.0) (10 3265.4599547511 6576.1686651584) (10 3265.6080316742 6553.5511312217) (10 3269.2307692308
6546.003280543))
((0 . "LWPOLYLINE") (100 . "AcDbEntity") (8 . "PLANTS") (62 . 94) (370 . 13) (100 . "AcDbPolyline") (90 . 2) (70 . 0)
(43 . 0.0) (10 3265.4599547511 6576.1686651584) (10 3273.9276295943 6578.9912234394))
((0 . "LWPOLYLINE") (100 . "AcDbEntity") (8 . "PLANTS") (62 . 94) (370 . 13) (100 . "AcDbPolyline") (90 . 3) (70 . 0)
(43 . 0.0) (10 3299.3966063348 414.782239819) (10 3275.7226244344 448.5635746606) (10 3265.4599547511 452.4886877828))
((0 . "LWPOLYLINE") (100 . "AcDbEntity") (8 . "PLANTS") (62 . 94) (370 . 13) (100 . "AcDbPolyline") (90 . 3) (70 . 0)
(43 . 0.0) (10 3286.1990950226 6772.2476244344) (10 3283.1093891403 6753.5485294118) (10 3269.2307692308
6749.6231900452))
((0 . "LWPOLYLINE") (100 . "AcDbEntity") (8 . "PLANTS") (62 . 94) (370 . 13) (100 . "AcDbPolyline") (90 . 3) (70 . 0)
(43 . 0.0) (10 3286.1990950226 6772.2476244344) (10 3287.8623303167 6779.7954751131) (10 3280.5429864253
6806.1842760181))
((0 . "LWPOLYLINE") (100 . "AcDbEntity") (8 . "PLANTS") (62 . 94) (370 . 13) (100 . "AcDbPolyline") (90 . 2) (70 . 0)
(43 . 0.0) (10 3284.313800905 6934.3891402715) (10 3314.4796380091 6896.6820135747))
((0 . "LWPOLYLINE") (100 . "AcDbEntity") (8 . "PLANTS") (62 . 94) (370 . 13) (100 . "AcDbPolyline") (90 . 2) (70 . 0)
(43 . 0.0) (10 3284.313800905 6934.3891402715) (10 3303.1674208145 6938.1596153846))
((0 . "LWPOLYLINE") (100 . "AcDbEntity") (8 . "PLANTS") (62 . 94) (370 . 13) (100 . "AcDbPolyline") (90 . 3) (70 . 0)
(43 . 0.0) (10 3286.1990950226 6772.2476244344) (10 3310.7088235294 6768.6312217195) (10 3329.5626696833
6783.559841629))
((0 . "LWPOLYLINE") (100 . "AcDbEntity") (8 . "PLANTS") (62 . 94) (370 . 13) (100 . "AcDbPolyline") (90 . 2) (70 . 0)
(43 . 0.0) (10 3288.0843891403 395.92760181) (10 3288.0843891403 369.5333710407))
((0 . "LWPOLYLINE") (100 . "AcDbEntity") (8 . "PLANTS") (62 . 94) (370 . 13) (100 . "AcDbPolyline") (90 . 2) (70 . 0)
(43 . 0.0) (10 3288.0843891403 395.92760181) (10 3299.3966063348 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3288.0843891403 369.5333710407 0.0) (10 3291.0742316341 342.8546457598 0.0) (10 3327.0160048695
306.1067440652 0.0) (10 3310.7088235294 275.2630090498 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3291.8552036199 565.6108597285 0.0) (10 3291.6561439349 540.1734643784 0.0) (10 3292.3706136653
506.5769269809 0.0) (10 3318.2504524887 493.967760181 0.0))
((0 . "LWPOLYLINE") (100 . "AcDbEntity") (8 . "PLANTS") (62 . 94) (370 . 13) (100 . "AcDbPolyline") (90 . 2) (70 . 0)
(43 . 0.0) (10 3291.8552036199 565.6108597285) (10 3303.1674208145 576.9230769231))
((0 . "LWPOLYLINE") (100 . "AcDbEntity") (8 . "PLANTS") (62 . 94) (370 . 13) (100 . "AcDbPolyline") (90 . 2) (70 . 0)
(43 . 0.0) (10 3299.3966063348 414.782239819) (10 3318.2504524887 414.782239819))
((0 . "LWPOLYLINE") (100 . "AcDbEntity") (8 . "PLANTS") (62 . 94) (370 . 13) (100 . "AcDbPolyline") (90 . 3) (70 . 0)
(43 . 0.0) (10 3333.3332579186 6904.2229638009) (10 3307.0929864253 6926.84739819) (10 3303.1674208145 6938.1596153846))
((0 . "LWPOLYLINE") (100 . "AcDbEntity") (8 . "PLANTS") (62 . 94) (370 . 13) (100 . "AcDbPolyline") (90 . 2) (70 . 0)
(43 . 0.0) (10 3318.2504524887 6960.7840497738) (10 3303.1674208145 6938.1596153846))
((0 . "LWPOLYLINE") (100 . "AcDbEntity") (8 . "PLANTS") (62 . 94) (370 . 13) (100 . "AcDbPolyline") (90 . 2) (70 . 0)
(43 . 0.0) (10 3314.4796380091 637.253959276) (10 3306.9382352941 622.1719457014))
((0 . "LWPOLYLINE") (100 . "AcDbEntity") (8 . "PLANTS") (62 . 94) (370 . 13) (100 . "AcDbPolyline") (90 . 2) (70 . 0)
(43 . 0.0) (10 3310.7088235294 275.2630090498) (10 3314.4796380091 248.8687782805))
((0 . "LWPOLYLINE") (100 . "AcDbEntity") (8 . "PLANTS") (62 . 94) (370 . 13) (100 . "AcDbPolyline") (90 . 2) (70 . 0)
(43 . 0.0) (10 3333.3332579186 6896.6820135747) (10 3314.4796380091 6896.6820135747))
((0 . "LWPOLYLINE") (100 . "AcDbEntity") (8 . "PLANTS") (62 . 94) (370 . 13) (100 . "AcDbPolyline") (90 . 3) (70 . 0)
(43 . 0.0) (10 3374.8115384615 248.8687782805) (10 3348.4162895928 241.3263574661) (10 3314.4796380091 248.8687782805))
((0 . "LWPOLYLINE") (100 . "AcDbEntity") (8 . "PLANTS") (62 . 94) (370 . 13) (100 . "AcDbPolyline") (90 . 3) (70 . 0)
(43 . 0.0) (10 3318.2504524887 493.967760181) (10 3314.486199095 471.3433257919) (10 3318.2504524887 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3344.6454751131 361.9909502262 0.0) (10 3323.6817812617 369.9080727625 0.0) (10 3335.4702084403
402.0106511628 0.0) (10 3318.2504524887 414.782239819 0.0))
((0 . "LWPOLYLINE") (100 . "AcDbEntity") (8 . "PLANTS") (62 . 94) (370 . 13) (100 . "AcDbPolyline") (90 . 3) (70 . 0)
(43 . 0.0) (10 3322.021040724 6825.0374434389) (10 3359.7285067873 6833.7769230769) (10 3374.8115384615
6847.6618778281))
((0 . "LWPOLYLINE") (100 . "AcDbEntity") (8 . "PLANTS") (62 . 94) (370 . 13) (100 . "AcDbPolyline") (90 . 2) (70 . 0)
(43 . 0.0) (10 3329.5626696833 6783.559841629) (10 3325.7918552036 6791.1007918552))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2317912773)
(40 . 0.2726408337) (40 . 1) (40 . 1) (40 . 1) (40 . 1) (10 3329.5626696833 6783.559841629 0.0) (10 3360.3413583756
6798.8752508541 0.0) (10 3392.7052374304 6780.93048801 0.0) (10 3516.1557261751 6785.9281872667 0.0) (10 3615.9094005058
6780.5826850804 0.0) (10 3706.6364253394 6779.7885746606 0.0))
((0 . "LWPOLYLINE") (100 . "AcDbEntity") (8 . "PLANTS") (62 . 94) (370 . 13) (100 . "AcDbPolyline") (90 . 2) (70 . 0)
(43 . 0.0) (10 3333.3332579186 6896.6820135747) (10 3333.3332579186 6904.2229638009))
((0 . "LWPOLYLINE") (100 . "AcDbEntity") (8 . "PLANTS") (62 . 94) (370 . 13) (100 . "AcDbPolyline") (90 . 3) (70 . 0)
(43 . 0.0) (10 3367.2699095023 6919.3064479638) (10 3348.4162895928 6914.3376696833) (10 3333.3332579186
6904.2229638009))
((0 . "LWPOLYLINE") (100 . "AcDbEntity") (8 . "PLANTS") (62 . 94) (370 . 13) (100 . "AcDbPolyline") (90 . 3) (70 . 0)
(43 . 0.0) (10 3333.3332579186 6896.6820135747) (10 3348.5643665158 6874.0575791855) (10 3374.8115384615
6847.6618778281))
((0 . "LWPOLYLINE") (100 . "AcDbEntity") (8 . "PLANTS") (62 . 94) (370 . 13) (100 . "AcDbPolyline") (90 . 2) (70 . 0)
(43 . 0.0) (10 3342.1864227726 7086.694225423) (10 3340.8748868778 7081.4479638009))
((0 . "LWPOLYLINE") (100 . "AcDbEntity") (8 . "PLANTS") (62 . 94) (370 . 13) (100 . "AcDbPolyline") (90 . 3) (70 . 0)
(43 . 0.0) (10 3344.6454751131 7043.7408371041) (10 3350.9961538462 7036.1925339367) (10 3355.9576923077
7013.5746606335))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3374.8115384615 275.2630090498 0.0) (10 3343.5896072425 290.2506724763 0.0) (10 3342.0485800293
333.6452525015 0.0) (10 3344.6454751131 361.9909502262 0.0))
((0 . "LWPOLYLINE") (100 . "AcDbEntity") (8 . "PLANTS") (62 . 94) (370 . 13) (100 . "AcDbPolyline") (90 . 2) (70 . 0)
(43 . 0.0) (10 3363.499321267 384.6153846154) (10 3344.6454751131 361.9909502262))
((0 . "LWPOLYLINE") (100 . "AcDbEntity") (8 . "PLANTS") (62 . 94) (370 . 13) (100 . "AcDbPolyline") (90 . 2) (70 . 0)
(43 . 0.0) (10 3397.4359728507 6975.8675339367) (10 3355.9576923077 7013.5746606335))
((0 . "LWPOLYLINE") (100 . "AcDbEntity") (8 . "PLANTS") (62 . 94) (370 . 13) (100 . "AcDbPolyline") (90 . 3) (70 . 0)
(43 . 0.0) (10 3367.2699095023 6919.3064479638) (10 3367.115158371 6934.3891402715) (10 3359.7285067873
6949.4718325792))
((0 . "LWPOLYLINE") (100 . "AcDbEntity") (8 . "PLANTS") (62 . 94) (370 . 13) (100 . "AcDbPolyline") (90 . 2) (70 . 0)
(43 . 0.0) (10 3378.5821266968 6919.3064479638) (10 3367.2699095023 6919.3064479638))
((0 . "LWPOLYLINE") (100 . "AcDbEntity") (8 . "PLANTS") (62 . 94) (370 . 13) (100 . "AcDbPolyline") (90 . 3) (70 . 0)
(43 . 0.0) (10 3420.0604072398 6851.4331447964) (10 3408.7478506787 6847.8101809955) (10 3374.8115384615
6847.6618778281))
((0 . "LWPOLYLINE") (100 . "AcDbEntity") (8 . "PLANTS") (62 . 94) (370 . 13) (100 . "AcDbPolyline") (90 . 2) (70 . 0)
(43 . 0.0) (10 3374.8115384615 275.2630090498) (10 3374.8115384615 248.8687782805))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4233954054) (40
. 1) (40 . 1) (40 . 1) (40 . 1) (10 3374.8115384616 275.2630090497 0.0) (10 3395.4268620723 292.3060625047 0.0) (10
3403.2266054826 349.4156054508 0.0) (10 3387.8662974355 414.1693959262 0.0) (10 3401.206561086 444.9462669683 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3374.8115384615 248.8687782805 0.0) (10 3390.6721273876 227.9420292081 0.0) (10 3424.8715489087
226.1467958751 0.0) (10 3442.684841629 245.0989819005 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3378.5821266968 6919.3064479638 0.0) (10 3401.6303342306 6906.4410941348 0.0) (10 3394.8817883031
6874.1661882479 0.0) (10 3420.0604072398 6862.745361991 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3378.5821266968 6919.3064479638 0.0) (10 3396.1573929918 6929.6932687505 0.0) (10 3423.3917131071
6939.1402393198 0.0) (10 3442.684841629 6926.84739819 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4041084225)
(40 . 0.8630099702) (40 . 1) (40 . 1) (40 . 1) (40 . 1) (10 3465.3092760181 6953.2430995475 0.0) (10 3449.0230797822
6959.3315489222 0.0) (10 3434.1252550516 6990.8260971285 0.0) (10 3388.7439464419 7013.8782857494 0.0) (10
3387.9232451883 7034.5965281346 0.0) (10 3389.8943438913 7039.9695701357 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3769035917) (40
. 1) (40 . 1) (40 . 1) (40 . 1) (10 3435.1432126697 516.59219457 0.0) (10 3475.5626878722 528.5335578852 0.0) (10
3519.1657813028 622.0182296754 0.0) (10 3523.1469323871 738.5284506873 0.0) (10 3559.1979893762 785.4266496147 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3408.1500726608 610.7818119963 0.0) (10 3385.3045971734 561.213760364 0.0) (10 3370.7442682707
492.408459464 0.0) (10 3401.2065610859 444.9462669683 0.0))
((0 . "LWPOLYLINE") (100 . "AcDbEntity") (8 . "PLANTS") (62 . 94) (370 . 13) (100 . "AcDbPolyline") (90 . 3) (70 . 0)
(43 . 0.0) (10 3435.1432126697 516.5921945701) (10 3422.6333710407 460.0311085973) (10 3401.206561086 444.9462669683))
((0 . "LWPOLYLINE") (100 . "AcDbEntity") (8 . "PLANTS") (62 . 94) (370 . 13) (100 . "AcDbPolyline") (90 . 3) (70 . 0)
(43 . 0.0) (10 3404.9773755656 7055.0530542986) (10 3412.5253393665 7058.6686651584) (10 3423.8309954751
7055.0530542986))
((0 . "LWPOLYLINE") (100 . "AcDbEntity") (8 . "PLANTS") (62 . 94) (370 . 13) (100 . "AcDbPolyline") (90 . 2) (70 . 0)
(43 . 0.0) (10 3420.0604072398 6862.745361991) (10 3420.0604072398 6851.4331447964))
((0 . "LWPOLYLINE") (100 . "AcDbEntity") (8 . "PLANTS") (62 . 94) (370 . 13) (100 . "AcDbPolyline") (90 . 2) (70 . 0)
(43 . 0.0) (10 3420.0604072398 6862.745361991) (10 3435.1432126697 6866.5158371041))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3529.4117647059 6836.3496606335 0.0) (10 3495.4070992119 6828.6947605629 0.0) (10 3443.9940727562
6816.2032369124 0.0) (10 3420.0604072398 6851.4331447964 0.0))
((0 . "LWPOLYLINE") (100 . "AcDbEntity") (8 . "PLANTS") (62 . 94) (370 . 13) (100 . "AcDbPolyline") (90 . 3) (70 . 0)
(43 . 0.0) (10 3435.1432126697 516.5921945701) (10 3428.7994343891 524.1393665158) (10 3427.6018099548 535.4440045249))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3431.3726244344 339.3665158371 0.0) (10 3428.057788655 366.310245546 0.0) (10 3458.680296296
398.1083068479 0.0) (10 3484.1628959276 377.0729638009 0.0))
((0 . "LWPOLYLINE") (100 . "AcDbEntity") (8 . "PLANTS") (62 . 94) (370 . 13) (100 . "AcDbPolyline") (90 . 2) (70 . 0)
(43 . 0.0) (10 3457.7676470588 6862.745361991) (10 3435.1432126697 6866.5158371041))
((0 . "LWPOLYLINE") (100 . "AcDbEntity") (8 . "PLANTS") (62 . 94) (370 . 13) (100 . "AcDbPolyline") (90 . 2) (70 . 0)
(43 . 0.0) (10 3442.684841629 6926.84739819) (10 3435.1432126697 6866.5158371041))
((0 . "LWPOLYLINE") (100 . "AcDbEntity") (8 . "PLANTS") (62 . 94) (370 . 13) (100 . "AcDbPolyline") (90 . 2) (70 . 0)
(43 . 0.0) (10 3442.684841629 6926.84739819) (10 3465.3092760181 6930.6186651584))
((0 . "LWPOLYLINE") (100 . "AcDbEntity") (8 . "PLANTS") (62 . 94) (370 . 13) (100 . "AcDbPolyline") (90 . 2) (70 . 0)
(43 . 0.0) (10 3442.684841629 263.9507918552) (10 3442.684841629 245.0989819005))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3442.684841629 263.9507918552 0.0) (10 3440.117167688 307.6589596364 0.0) (10 3490.2749514899
330.8658005386 0.0) (10 3484.1628959276 377.0729638009 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3442.684841629 263.9507918552 0.0) (10 3498.8962455677 264.7180938417 0.0) (10 3507.12527849
339.6032245296 0.0) (10 3559.57760181 350.6787330316 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3574.6606334842 241.3263574661 0.0) (10 3535.8582655611 217.7288120682 0.0) (10 3480.4950914631
220.7429620318 0.0) (10 3442.684841629 245.0989819005 0.0))
((0 . "LWPOLYLINE") (100 . "AcDbEntity") (8 . "PLANTS") (62 . 94) (370 . 13) (100 . "AcDbPolyline") (90 . 3) (70 . 0)
(43 . 0.0) (10 3472.850678733 467.5707013575) (10 3461.5450226244 475.1193438914) (10 3453.9970588235 486.4253393665))
((0 . "LWPOLYLINE") (100 . "AcDbEntity") (8 . "PLANTS") (62 . 94) (370 . 13) (100 . "AcDbPolyline") (90 . 2) (70 . 0)
(43 . 0.0) (10 3465.3092760181 6953.2430995475) (10 3465.3092760181 6930.6186651584))
((0 . "LWPOLYLINE") (100 . "AcDbEntity") (8 . "PLANTS") (62 . 94) (370 . 13) (100 . "AcDbPolyline") (90 . 2) (70 . 0)
(43 . 0.0) (10 3465.3092760181 6953.2430995475) (10 3484.1628959276 6960.7840497738))
((0 . "LWPOLYLINE") (100 . "AcDbEntity") (8 . "PLANTS") (62 . 94) (370 . 13) (100 . "AcDbPolyline") (90 . 3) (70 . 0)
(43 . 0.0) (10 3527.5264705882 6896.6820135747) (10 3487.9337104072 6909.1917420814) (10 3465.3092760181
6930.6186651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3495.4751131222 6981.5236425339 0.0) (10 3475.8346641947 6975.0514404874 0.0) (10 3469.7104976341
7021.6715270438 0.0) (10 3476.6214932127 7024.8868778281 0.0))
((0 . "LWPOLYLINE") (100 . "AcDbEntity") (8 . "PLANTS") (62 . 94) (370 . 13) (100 . "AcDbPolyline") (90 . 3) (70 . 0)
(43 . 0.0) (10 3484.1628959276 6960.7840497738) (10 3487.9337104072 6957.0135746606) (10 3491.7042986425
6964.5553167421))
((0 . "LWPOLYLINE") (100 . "AcDbEntity") (8 . "PLANTS") (62 . 94) (370 . 13) (100 . "AcDbPolyline") (90 . 2) (70 . 0)
(43 . 0.0) (10 3484.1628959276 6960.7840497738) (10 3491.7042986425 6964.5553167421))
((0 . "LWPOLYLINE") (100 . "AcDbEntity") (8 . "PLANTS") (62 . 94) (370 . 13) (100 . "AcDbPolyline") (90 . 2) (70 . 0)
(43 . 0.0) (10 3491.7042986425 384.6153846154) (10 3484.1628959276 377.0729638009))
((0 . "LWPOLYLINE") (100 . "AcDbEntity") (8 . "PLANTS") (62 . 94) (370 . 13) (100 . "AcDbPolyline") (90 . 2) (70 . 0)
(43 . 0.0) (10 3495.4751131222 6981.5236425339) (10 3491.7042986425 6964.5553167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3491.7042986425 384.6153846154 0.0) (10 3464.5156362369 424.0968620484 0.0) (10 3526.9115944861
466.9626165665 0.0) (10 3535.7995103677 497.7375565611 0.0))
((0 . "LWPOLYLINE") (100 . "AcDbEntity") (8 . "PLANTS") (62 . 94) (370 . 13) (100 . "AcDbPolyline") (90 . 3) (70 . 0)
(43 . 0.0) (10 3491.7042986425 384.6153846154) (10 3529.4117647059 404.5187782805) (10 3559.57760181 433.6340497738))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3495.4751131222 6981.5236425339 0.0) (10 3518.8602412555 6973.005127041 0.0) (10 3511.7102295646
6938.9121827019 0.0) (10 3533.1825791855 6930.6186651584 0.0))
((0 . "SPLINE") (100 . "AcDbEntity") (8 . "PLANTS") (62 . 94) (370 . 13) (100 . "AcDbSpline") (70 . 3) (71 . 3) (72 .
10) (73 . 6) (74 . 0) (42 . 0.0000001) (43 . 0.0000001) (40 . -1) (40 . -0.7198000654) (40 . -0.5) (40 . 0.0) (40 .
0.2801999346) (40 . 0.5) (40 . 1) (40 . 1.2801999346) (40 . 1.5) (40 . 2) (10 3497.533665524 6993.9003721067 0.0) (10
3497.1014005807 6976.0094361595 0.0) (10 3491.890331159 6987.5995570784 0.0) (10 3497.533665524 6993.9003721067 0.0) (10
3497.1014005807 6976.0094361595 0.0) (10 3491.890331159 6987.5995570784 0.0))
((0 . "LWPOLYLINE") (100 . "AcDbEntity") (8 . "PLANTS") (62 . 94) (370 . 13) (100 . "AcDbPolyline") (90 . 3) (70 . 0)
(43 . 0.0) (10 3495.4751131222 6981.5236425339) (10 3506.6458144796 6983.6374434389) (10 3533.1825791855
7009.8041855204))
((0 . "LWPOLYLINE") (100 . "AcDbEntity") (8 . "PLANTS") (62 . 94) (370 . 13) (100 . "AcDbPolyline") (90 . 3) (70 . 0)
(43 . 0.0) (10 3506.7873303167 7066.3652714932) (10 3503.0165158371 7062.5940045249) (10 3514.3287330317
7051.2817873303))
((0 . "LWPOLYLINE") (100 . "AcDbEntity") (8 . "PLANTS") (62 . 94) (370 . 13) (100 . "AcDbPolyline") (90 . 3) (70 . 0)
(43 . 0.0) (10 3574.6606334842 260.1809954751) (10 3548.2653846154 271.3447963801) (10 3525.6409502262 267.7234162896))
((0 . "LWPOLYLINE") (100 . "AcDbEntity") (8 . "PLANTS") (62 . 94) (370 . 13) (100 . "AcDbPolyline") (90 . 2) (70 . 0)
(43 . 0.0) (10 3527.5264705882 6896.6820135747) (10 3529.4117647059 6836.3496606335))
((0 . "LWPOLYLINE") (100 . "AcDbEntity") (8 . "PLANTS") (62 . 94) (370 . 13) (100 . "AcDbPolyline") (90 . 2) (70 . 0)
(43 . 0.0) (10 3527.5264705882 6896.6820135747) (10 3533.1825791855 6930.6186651584))
((0 . "LWPOLYLINE") (100 . "AcDbEntity") (8 . "PLANTS") (62 . 94) (370 . 13) (100 . "AcDbPolyline") (90 . 3) (70 . 0)
(43 . 0.0) (10 3527.5264705882 6896.6820135747) (10 3574.6606334842 6901.9692307692) (10 3612.3680995475
6874.0575791855))
((0 . "LWPOLYLINE") (100 . "AcDbEntity") (8 . "PLANTS") (62 . 94) (370 . 13) (100 . "AcDbPolyline") (90 . 3) (70 . 0)
(43 . 0.0) (10 3529.4117647059 6836.3496606335) (10 3567.1192307692 6836.4979638009) (10 3612.3680995475
6851.4331447964))
((0 . "LWPOLYLINE") (100 . "AcDbEntity") (8 . "PLANTS") (62 . 94) (370 . 13) (100 . "AcDbPolyline") (90 . 2) (70 . 0)
(43 . 0.0) (10 3578.4314479638 6953.2430995475) (10 3533.1825791855 6930.6186651584))
((0 . "LWPOLYLINE") (100 . "AcDbEntity") (8 . "PLANTS") (62 . 94) (370 . 13) (100 . "AcDbPolyline") (90 . 2) (70 . 0)
(43 . 0.0) (10 3616.1386877828 6730.7692307692) (10 3567.1192307692 6730.7692307692))
((0 . "LWPOLYLINE") (100 . "AcDbEntity") (8 . "PLANTS") (62 . 94) (370 . 13) (100 . "AcDbPolyline") (90 . 2) (70 . 0)
(43 . 0.0) (10 3567.1192307692 6730.7692307692) (10 3559.57760181 6730.7692307692))
((0 . "LWPOLYLINE") (100 . "AcDbEntity") (8 . "PLANTS") (62 . 94) (370 . 13) (100 . "AcDbPolyline") (90 . 2) (70 . 0)
(43 . 0.0) (10 3559.57760181 6730.7692307692) (10 3548.2653846154 6730.7692307692))
((0 . "LWPOLYLINE") (100 . "AcDbEntity") (8 . "PLANTS") (62 . 94) (370 . 13) (100 . "AcDbPolyline") (90 . 2) (70 . 0)
(43 . 0.0) (10 3548.2653846154 6730.7692307692) (10 3540.7239819005 6730.7692307692))
((0 . "LWPOLYLINE") (100 . "AcDbEntity") (8 . "PLANTS") (62 . 94) (370 . 13) (100 . "AcDbPolyline") (90 . 2) (70 . 0)
(43 . 0.0) (10 3540.7239819005 6730.7692307692) (10 3533.1825791855 6730.7692307692))
((0 . "LWPOLYLINE") (100 . "AcDbEntity") (8 . "PLANTS") (62 . 94) (370 . 13) (100 . "AcDbPolyline") (90 . 3) (70 . 0)
(43 . 0.0) (10 3589.7436651584 482.6555429864) (10 3568.175678733 460.0311085973) (10 3559.57760181 433.6340497738))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3559.57760181 433.6340497737 0.0) (10 3613.1146405357 473.3962404023 0.0) (10 3678.5404916464
458.5453184216 0.0) (10 3736.8024886878 478.882918552 0.0))
((0 . "LWPOLYLINE") (100 . "AcDbEntity") (8 . "PLANTS") (62 . 94) (370 . 13) (100 . "AcDbPolyline") (90 . 3) (70 . 0)
(43 . 0.0) (10 3578.4314479638 328.0542986425) (10 3571.0313348416 331.9794117647) (10 3559.57760181 350.6787330317))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3593.5142533937 331.8240950226 0.0) (10 3599.5686725713 351.9918685075 0.0) (10 3571.3419593179
368.8655604577 0.0) (10 3559.5776018099 350.6787330317 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3604.8264705883 6994.7207013575 0.0) (10 3566.4422785316 6988.0510867464 0.0) (10 3548.2601295528
7042.1236992033 0.0) (10 3567.1192307692 7070.1357466063 0.0))
((0 . "LWPOLYLINE") (100 . "AcDbEntity") (8 . "PLANTS") (62 . 94) (370 . 13) (100 . "AcDbPolyline") (90 . 2) (70 . 0)
(43 . 0.0) (10 3574.6606334842 241.3263574661) (10 3574.6606334842 260.1809954751))
((0 . "LWPOLYLINE") (100 . "AcDbEntity") (8 . "PLANTS") (62 . 94) (370 . 13) (100 . "AcDbPolyline") (90 . 2) (70 . 0)
(43 . 0.0) (10 3597.2850678733 290.3478506787) (10 3574.6606334842 260.1809954751))
((0 . "LWPOLYLINE") (100 . "AcDbEntity") (8 . "PLANTS") (62 . 94) (370 . 13) (100 . "AcDbPolyline") (90 . 3) (70 . 0)
(43 . 0.0) (10 3574.6606334842 241.3263574661) (10 3623.6803167421 237.7049773756) (10 3638.7631221719 245.0989819005))
((0 . "LWPOLYLINE") (100 . "AcDbEntity") (8 . "PLANTS") (62 . 94) (370 . 13) (100 . "AcDbPolyline") (90 . 2) (70 . 0)
(43 . 0.0) (10 3597.2850678733 6949.4718325792) (10 3578.4314479638 6953.2430995475))
((0 . "LWPOLYLINE") (100 . "AcDbEntity") (8 . "PLANTS") (62 . 94) (370 . 13) (100 . "AcDbPolyline") (90 . 2) (70 . 0)
(43 . 0.0) (10 3582.2020361991 6972.0962669683) (10 3578.4314479638 6953.2430995475))
((0 . "LWPOLYLINE") (100 . "AcDbEntity") (8 . "PLANTS") (62 . 94) (370 . 13) (100 . "AcDbPolyline") (90 . 3) (70 . 0)
(43 . 0.0) (10 3578.4314479638 328.0542986425) (10 3579.6356334842 309.1996606335) (10 3597.2850678733 290.3478506787))
((0 . "LWPOLYLINE") (100 . "AcDbEntity") (8 . "PLANTS") (62 . 94) (370 . 13) (100 . "AcDbPolyline") (90 . 3) (70 . 0)
(43 . 0.0) (10 3593.5142533937 331.8240950226) (10 3582.2020361991 331.8240950226) (10 3578.4314479638 328.0542986425))
((0 . "LWPOLYLINE") (100 . "AcDbEntity") (8 . "PLANTS") (62 . 94) (370 . 13) (100 . "AcDbPolyline") (90 . 2) (70 . 0)
(43 . 0.0) (10 3590.9478506787 497.7375565611) (10 3589.7436651584 482.6555429864))
((0 . "LWPOLYLINE") (100 . "AcDbEntity") (8 . "PLANTS") (62 . 94) (370 . 13) (100 . "AcDbPolyline") (90 . 3) (70 . 0)
(43 . 0.0) (10 3589.7436651584 482.6555429864) (10 3608.5972850679 483.8527149321) (10 3626.1095025877 497.7375565611))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3604.8264705882 7141.7795248869 0.0) (10 3586.0105084403 7137.9295541743 0.0) (10 3574.518752879
7102.7858745955 0.0) (10 3593.5142533937 7092.7601809955 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3593.5142533937 331.8240950226 0.0) (10 3613.6807403532 332.1957623595 0.0) (10 3615.181938375
302.8590505385 0.0) (10 3612.3680995475 290.3478506787 0.0))
((0 . "LWPOLYLINE") (100 . "AcDbEntity") (8 . "PLANTS") (62 . 94) (370 . 13) (100 . "AcDbPolyline") (90 . 3) (70 . 0)
(43 . 0.0) (10 3597.2850678733 6949.4718325792) (10 3598.4895927602 6930.6186651584) (10 3616.1386877828
6915.5351809955))
((0 . "LWPOLYLINE") (100 . "AcDbEntity") (8 . "PLANTS") (62 . 94) (370 . 13) (100 . "AcDbPolyline") (90 . 3) (70 . 0)
(43 . 0.0) (10 3597.2850678733 6949.4718325792) (10 3615.9839366516 6960.7909502262) (10 3619.9095022624
6975.8675339367))
((0 . "LWPOLYLINE") (100 . "AcDbEntity") (8 . "PLANTS") (62 . 94) (370 . 13) (100 . "AcDbPolyline") (90 . 2) (70 . 0)
(43 . 0.0) (10 3612.3680995475 290.3478506787) (10 3597.2850678733 290.3478506787))
((0 . "LWPOLYLINE") (100 . "AcDbEntity") (8 . "PLANTS") (62 . 94) (370 . 13) (100 . "AcDbPolyline") (90 . 2) (70 . 0)
(43 . 0.0) (10 3604.8264705882 6994.7207013575) (10 3619.9095022624 6975.8675339367))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3604.8264705882 6994.7207013575 0.0) (10 3623.2668926753 7013.7175327134 0.0) (10 3594.4181116788
7037.2437944542 0.0) (10 3608.5972850679 7055.0530542986 0.0))
((0 . "LWPOLYLINE") (100 . "AcDbEntity") (8 . "PLANTS") (62 . 94) (370 . 13) (100 . "AcDbPolyline") (90 . 2) (70 . 0)
(43 . 0.0) (10 3612.3680995475 6874.0575791855) (10 3612.3680995475 6851.4331447964))
((0 . "LWPOLYLINE") (100 . "AcDbEntity") (8 . "PLANTS") (62 . 94) (370 . 13) (100 . "AcDbPolyline") (90 . 2) (70 . 0)
(43 . 0.0) (10 3616.1386877828 6881.5985294118) (10 3612.3680995475 6874.0575791855))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3676.4705882353 6847.6618778281 0.0) (10 3656.2056631416 6839.6757132924 0.0) (10 3630.676207946
6838.1044282252 0.0) (10 3612.3680995475 6851.4331447964 0.0))
((0 . "LWPOLYLINE") (100 . "AcDbEntity") (8 . "PLANTS") (62 . 94) (370 . 13) (100 . "AcDbPolyline") (90 . 2) (70 . 0)
(43 . 0.0) (10 3638.7631221719 267.7234162896) (10 3612.3680995475 290.3478506787))
((0 . "LWPOLYLINE") (100 . "AcDbEntity") (8 . "PLANTS") (62 . 94) (370 . 13) (100 . "AcDbPolyline") (90 . 2) (70 . 0)
(43 . 0.0) (10 3616.1386877828 6881.5985294118) (10 3616.1386877828 6915.5351809955))
((0 . "LWPOLYLINE") (100 . "AcDbEntity") (8 . "PLANTS") (62 . 94) (370 . 13) (100 . "AcDbPolyline") (90 . 2) (70 . 0)
(43 . 0.0) (10 3638.7631221719 6919.3064479638) (10 3616.1386877828 6915.5351809955))
((0 . "LWPOLYLINE") (100 . "AcDbEntity") (8 . "PLANTS") (62 . 94) (370 . 13) (100 . "AcDbPolyline") (90 . 3) (70 . 0)
(43 . 0.0) (10 3650.0753393665 6900.4524886878) (10 3638.7631221719 6890.3378959276) (10 3616.1386877828
6881.5985294118))
((0 . "LWPOLYLINE") (100 . "AcDbEntity") (8 . "PLANTS") (62 . 94) (370 . 13) (100 . "AcDbPolyline") (90 . 2) (70 . 0)
(43 . 0.0) (10 3642.5339366516 6983.4084841629) (10 3619.9095022624 6975.8675339367))
((0 . "LWPOLYLINE") (100 . "AcDbEntity") (8 . "PLANTS") (62 . 94) (370 . 13) (100 . "AcDbPolyline") (90 . 3) (70 . 0)
(43 . 0.0) (10 3646.3047511312 7077.6774886878) (10 3621.2555429864 7111.607239819) (10 3623.6803167421
7119.1550904977))
((0 . "LWPOLYLINE") (100 . "AcDbEntity") (8 . "PLANTS") (62 . 94) (370 . 13) (100 . "AcDbPolyline") (90 . 2) (70 . 0)
(43 . 0.0) (10 3638.7631221719 6919.3064479638) (10 3650.0753393665 6900.4524886878))
((0 . "LWPOLYLINE") (100 . "AcDbEntity") (8 . "PLANTS") (62 . 94) (370 . 13) (100 . "AcDbPolyline") (90 . 3) (70 . 0)
(43 . 0.0) (10 3638.7631221719 6919.3064479638) (10 3646.4529411765 6938.0052036199) (10 3657.6169683258
6941.9308823529))
((0 . "LWPOLYLINE") (100 . "AcDbEntity") (8 . "PLANTS") (62 . 94) (370 . 13) (100 . "AcDbPolyline") (90 . 2) (70 . 0)
(43 . 0.0) (10 3638.7631221719 267.7234162896) (10 3638.7631221719 245.0989819005))
((0 . "LWPOLYLINE") (100 . "AcDbEntity") (8 . "PLANTS") (62 . 94) (370 . 13) (100 . "AcDbPolyline") (90 . 2) (70 . 0)
(43 . 0.0) (10 3638.7631221719 267.7234162896) (10 3661.3875565611 286.5752262443))
((0 . "LWPOLYLINE") (100 . "AcDbEntity") (8 . "PLANTS") (62 . 94) (370 . 13) (100 . "AcDbPolyline") (90 . 2) (70 . 0)
(43 . 0.0) (10 3691.5536199095 245.0989819005) (10 3638.7631221719 245.0989819005))
((0 . "LWPOLYLINE") (100 . "AcDbEntity") (8 . "PLANTS") (62 . 94) (370 . 13) (100 . "AcDbPolyline") (90 . 3) (70 . 0)
(43 . 0.0) (10 3691.5536199095 7002.2624434389) (10 3668.9226244344 6982.6617647059) (10 3642.5339366516
6983.4084841629))
((0 . "LWPOLYLINE") (100 . "AcDbEntity") (8 . "PLANTS") (62 . 94) (370 . 13) (100 . "AcDbPolyline") (90 . 2) (70 . 0)
(43 . 0.0) (10 3646.3047511312 7077.6774886878) (10 3642.5339366516 6983.4084841629))
((0 . "LWPOLYLINE") (100 . "AcDbEntity") (8 . "PLANTS") (62 . 94) (370 . 13) (100 . "AcDbPolyline") (90 . 2) (70 . 0)
(43 . 0.0) (10 3646.3047511312 7077.6774886878) (10 3657.6169683258 7081.4479638009))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3661.3875565611 286.5752262443 0.0) (10 3669.4779050145 310.8907691307 0.0) (10 3641.7411611078
326.8359986183 0.0) (10 3646.3047511312 350.6787330317 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3646.3047511312 350.6787330317 0.0) (10 3612.4529384459 344.5231748915 0.0) (10 3628.3169377158
405.243614264 0.0) (10 3653.8461538462 373.3031674208 0.0))
((0 . "LWPOLYLINE") (100 . "AcDbEntity") (8 . "PLANTS") (62 . 94) (370 . 13) (100 . "AcDbPolyline") (90 . 2) (70 . 0)
(43 . 0.0) (10 3646.3047511312 350.6787330317) (10 3653.8461538462 373.3031674208))
((0 . "LWPOLYLINE") (100 . "AcDbEntity") (8 . "PLANTS") (62 . 94) (370 . 13) (100 . "AcDbPolyline") (90 . 2) (70 . 0)
(43 . 0.0) (10 3650.0753393665 6900.4524886878) (10 3676.4705882353 6896.6820135747))
((0 . "LWPOLYLINE") (100 . "AcDbEntity") (8 . "PLANTS") (62 . 94) (370 . 13) (100 . "AcDbPolyline") (90 . 2) (70 . 0)
(43 . 0.0) (10 3684.0119909502 380.8455882353) (10 3653.8461538462 373.3031674208))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3661.3875565611 286.5752262443 0.0) (10 3678.9489788611 291.0062799581 0.0) (10 3687.2733957552
267.2997521519 0.0) (10 3691.5536199095 256.411199095 0.0))
((0 . "LWPOLYLINE") (100 . "AcDbEntity") (8 . "PLANTS") (62 . 94) (370 . 13) (100 . "AcDbPolyline") (90 . 2) (70 . 0)
(43 . 0.0) (10 3680.2414027149 6885.3697963801) (10 3676.4705882353 6896.6820135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3717.9486425339 6957.0135746606 0.0) (10 3693.4872975755 6948.634607806 0.0) (10 3670.152511714
6926.7196908162 0.0) (10 3676.4705882353 6896.6820135747 0.0))
((0 . "LWPOLYLINE") (100 . "AcDbEntity") (8 . "PLANTS") (62 . 94) (370 . 13) (100 . "AcDbPolyline") (90 . 3) (70 . 0)
(43 . 0.0) (10 3676.4705882353 6847.6618778281) (10 3691.5536199095 6833.7834841629) (10 3710.407239819
6828.8087104072))
((0 . "LWPOLYLINE") (100 . "AcDbEntity") (8 . "PLANTS") (62 . 94) (370 . 13) (100 . "AcDbPolyline") (90 . 3) (70 . 0)
(43 . 0.0) (10 3676.4705882353 6847.6618778281) (10 3676.6186651584 6877.8214932127) (10 3680.2414027149
6885.3697963801))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3680.2414027149 6885.3697963801 0.0) (10 3700.1633061899 6903.8158834871 0.0) (10 3734.7158237435
6907.9967332997 0.0) (10 3755.6561085973 6889.1402714932 0.0))
((0 . "LWPOLYLINE") (100 . "AcDbEntity") (8 . "PLANTS") (62 . 94) (370 . 13) (100 . "AcDbPolyline") (90 . 2) (70 . 0)
(43 . 0.0) (10 3702.8658371041 377.0729638009) (10 3684.0119909502 380.8455882353))
((0 . "LWPOLYLINE") (100 . "AcDbEntity") (8 . "PLANTS") (62 . 94) (370 . 13) (100 . "AcDbPolyline") (90 . 2) (70 . 0)
(43 . 0.0) (10 3684.0119909502 380.8455882353) (10 3687.7828054299 422.3218325792))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3702.8658371041 377.0729638009 0.0) (10 3709.9594162757 359.331790159 0.0) (10 3707.3707507202
328.3085486938 0.0) (10 3684.0119909502 324.2845022624 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3691.5535067873 7162.5544309741 0.0) (10 3691.5537662673 7114.1513325656 0.0) (10 3691.5532153622
7065.7482341547 0.0) (10 3691.5536199095 7017.3451357466 0.0))
((0 . "LWPOLYLINE") (100 . "AcDbEntity") (8 . "PLANTS") (62 . 94) (370 . 13) (100 . "AcDbPolyline") (90 . 2) (70 . 0)
(43 . 0.0) (10 3691.5536199095 7002.2624434389) (10 3691.5536199095 7017.3451357466))
((0 . "LWPOLYLINE") (100 . "AcDbEntity") (8 . "PLANTS") (62 . 94) (370 . 13) (100 . "AcDbPolyline") (90 . 3) (70 . 0)
(43 . 0.0) (10 3733.0316742081 7036.1990950226) (10 3725.3421945701 7022.3207013575) (10 3691.5536199095
7017.3451357466))
((0 . "LWPOLYLINE") (100 . "AcDbEntity") (8 . "PLANTS") (62 . 94) (370 . 13) (100 . "AcDbPolyline") (90 . 2) (70 . 0)
(43 . 0.0) (10 3717.9486425339 6972.0962669683) (10 3691.5536199095 7002.2624434389))
((0 . "LWPOLYLINE") (100 . "AcDbEntity") (8 . "PLANTS") (62 . 94) (370 . 13) (100 . "AcDbPolyline") (90 . 2) (70 . 0)
(43 . 0.0) (10 3691.5536199095 6730.7692307692) (10 3706.6364253394 6745.8519230769))
((0 . "LWPOLYLINE") (100 . "AcDbEntity") (8 . "PLANTS") (62 . 94) (370 . 13) (100 . "AcDbPolyline") (90 . 2) (70 . 0)
(43 . 0.0) (10 3691.5536199095 245.0989819005) (10 3691.5536199095 256.411199095))
((0 . "LWPOLYLINE") (100 . "AcDbEntity") (8 . "PLANTS") (62 . 94) (370 . 13) (100 . "AcDbPolyline") (90 . 3) (70 . 0)
(43 . 0.0) (10 3691.5536199095 256.411199095) (10 3733.0316742081 272.5495475113) (10 3751.8852941176 290.3478506787))
((0 . "LWPOLYLINE") (100 . "AcDbEntity") (8 . "PLANTS") (62 . 94) (370 . 13) (100 . "AcDbPolyline") (90 . 3) (70 . 0)
(43 . 0.0) (10 3691.5536199095 245.0989819005) (10 3714.1780542986 230.1625565611) (10 3804.6761312217 237.556561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3702.8658371041 377.0729638009 0.0) (10 3723.1668647896 393.2831316219 0.0) (10 3743.2694504678
348.7632010929 0.0) (10 3766.9683257919 369.5333710407 0.0))
((0 . "LWPOLYLINE") (100 . "AcDbEntity") (8 . "PLANTS") (62 . 94) (370 . 13) (100 . "AcDbPolyline") (90 . 2) (70 . 0)
(43 . 0.0) (10 3706.6364253394 6779.7885746606) (10 3751.8852941176 6776.0180995475))
((0 . "LWPOLYLINE") (100 . "AcDbEntity") (8 . "PLANTS") (62 . 94) (370 . 13) (100 . "AcDbPolyline") (90 . 2) (70 . 0)
(43 . 0.0) (10 3706.6364253394 6779.7885746606) (10 3710.407239819 6828.8087104072))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4358261144) (40
. 1) (40 . 1) (40 . 1) (40 . 1) (10 3710.4072398191 6828.8087104072 0.0) (10 3718.9840537572 6835.7573143753 0.0) (10
3732.1899096075 6857.7228726503 0.0) (10 3752.7155726053 6873.9512718008 0.0) (10 3755.6561085973 6889.1402714932 0.0))
((0 . "LWPOLYLINE") (100 . "AcDbEntity") (8 . "PLANTS") (62 . 94) (370 . 13) (100 . "AcDbPolyline") (90 . 2) (70 . 0)
(43 . 0.0) (10 3717.9486425339 6972.0962669683) (10 3717.9486425339 6957.0135746606))
((0 . "LWPOLYLINE") (100 . "AcDbEntity") (8 . "PLANTS") (62 . 94) (370 . 13) (100 . "AcDbPolyline") (90 . 3) (70 . 0)
(43 . 0.0) (10 3717.9486425339 6972.0962669683) (10 3748.1081447964 6997.2876696833) (10 3755.6561085973
6998.4919683258))
((0 . "LWPOLYLINE") (100 . "AcDbEntity") (8 . "PLANTS") (62 . 94) (370 . 13) (100 . "AcDbPolyline") (90 . 3) (70 . 0)
(43 . 0.0) (10 3785.8216063348 6911.7647058824) (10 3774.3615384615 6933.3331447964) (10 3717.9486425339
6957.0135746606))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3140388277) (40
. 1) (40 . 1) (40 . 1) (40 . 1) (10 3793.3639140273 7039.9695701359 0.0) (10 3793.3333566243 7049.6900792059 0.0) (10
3753.5184111781 7040.9514398778 0.0) (10 3746.7798228567 7088.6097047226 0.0) (10 3721.7194570136 7088.9897058824 0.0))
((0 . "LWPOLYLINE") (100 . "AcDbEntity") (8 . "PLANTS") (62 . 94) (370 . 13) (100 . "AcDbPolyline") (90 . 2) (70 . 0)
(43 . 0.0) (10 3748.1147058824 6738.3109728507) (10 3733.1992881764 6730.7692307692))
((0 . "LWPOLYLINE") (100 . "AcDbEntity") (8 . "PLANTS") (62 . 94) (370 . 13) (100 . "AcDbPolyline") (90 . 2) (70 . 0)
(43 . 0.0) (10 3804.6761312217 6579.9399321267) (10 3791.4772209369 6614.1994843161))
((0 . "LWPOLYLINE") (100 . "AcDbEntity") (8 . "PLANTS") (62 . 94) (370 . 13) (100 . "AcDbPolyline") (90 . 3) (70 . 0)
(43 . 0.0) (10 3914.0271493213 6478.129638009) (10 3887.631561086 6478.1297511312) (10 3805.3148209218 6478.1297511312))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3698607943) (40
. 1) (40 . 1) (40 . 1) (40 . 1) (10 3793.3639140271 426.0944570135 0.0) (10 3785.9639477248 432.1916442369 0.0) (10
3771.1125609548 453.8776006547 0.0) (10 3743.1183139932 460.4087799785 0.0) (10 3736.8024886878 478.882918552 0.0))
((0 . "LWPOLYLINE") (100 . "AcDbEntity") (8 . "PLANTS") (62 . 94) (370 . 13) (100 . "AcDbPolyline") (90 . 2) (70 . 0)
(43 . 0.0) (10 3744.3438914027 493.967760181) (10 3736.8024886878 478.882918552))
((0 . "LWPOLYLINE") (100 . "AcDbEntity") (8 . "PLANTS") (62 . 94) (370 . 13) (100 . "AcDbPolyline") (90 . 2) (70 . 0)
(43 . 0.0) (10 3748.1147058824 316.742081448) (10 3740.5730769231 320.5118778281))
((0 . "LWPOLYLINE") (100 . "AcDbEntity") (8 . "PLANTS") (62 . 94) (370 . 13) (100 . "AcDbPolyline") (90 . 2) (70 . 0)
(43 . 0.0) (10 3748.1147058824 6738.3109728507) (10 3758.1702614344 6730.7692307692))
((0 . "LWPOLYLINE") (100 . "AcDbEntity") (8 . "PLANTS") (62 . 94) (370 . 13) (100 . "AcDbPolyline") (90 . 2) (70 . 0)
(43 . 0.0) (10 3748.1147058824 6738.3109728507) (10 3751.8852941176 6776.0180995475))
((0 . "LWPOLYLINE") (100 . "AcDbEntity") (8 . "PLANTS") (62 . 94) (370 . 13) (100 . "AcDbPolyline") (90 . 2) (70 . 0)
(43 . 0.0) (10 3748.1147058824 316.742081448) (10 3751.8852941176 290.3478506787))
((0 . "LWPOLYLINE") (100 . "AcDbEntity") (8 . "PLANTS") (62 . 94) (370 . 13) (100 . "AcDbPolyline") (90 . 2) (70 . 0)
(43 . 0.0) (10 3748.1147058824 316.742081448) (10 3755.6561085973 320.5118778281))
((0 . "LWPOLYLINE") (100 . "AcDbEntity") (8 . "PLANTS") (62 . 94) (370 . 13) (100 . "AcDbPolyline") (90 . 2) (70 . 0)
(43 . 0.0) (10 3782.0513574661 6776.0180995475) (10 3751.8852941176 6776.0180995475))
((0 . "LWPOLYLINE") (100 . "AcDbEntity") (8 . "PLANTS") (62 . 94) (370 . 13) (100 . "AcDbPolyline") (90 . 3) (70 . 0)
(43 . 0.0) (10 3751.8852941176 6776.0180995475) (10 3752.0399321267 6806.1839366516) (10 3763.1975113122
6817.4964932127))
((0 . "LWPOLYLINE") (100 . "AcDbEntity") (8 . "PLANTS") (62 . 94) (370 . 13) (100 . "AcDbPolyline") (90 . 3) (70 . 0)
(43 . 0.0) (10 3766.9683257919 369.5333710407) (10 3765.7641402715 388.3851809955) (10 3751.8852941176 407.2398190045))
((0 . "LWPOLYLINE") (100 . "AcDbEntity") (8 . "PLANTS") (62 . 94) (370 . 13) (100 . "AcDbPolyline") (90 . 2) (70 . 0)
(43 . 0.0) (10 3751.8852941176 290.3478506787) (10 3812.2171945701 297.8874434389))
((0 . "LWPOLYLINE") (100 . "AcDbEntity") (8 . "PLANTS") (62 . 94) (370 . 13) (100 . "AcDbPolyline") (90 . 3) (70 . 0)
(43 . 0.0) (10 3755.6561085973 6998.4919683258) (10 3763.3521493213 6983.4153846154) (10 3774.5097285068
6975.8675339367))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3755.6561085973 6998.4919683258 0.0) (10 3771.2902269005 7030.1583178902 0.0) (10 3829.9178218396
6993.5508139726 0.0) (10 3812.2171945701 6960.7840497738 0.0))
((0 . "LWPOLYLINE") (100 . "AcDbEntity") (8 . "PLANTS") (62 . 94) (370 . 13) (100 . "AcDbPolyline") (90 . 3) (70 . 0)
(43 . 0.0) (10 3785.8216063348 6911.7647058824) (10 3774.5097285068 6897.7380090498) (10 3755.6561085973
6889.1402714932))
((0 . "LWPOLYLINE") (100 . "AcDbEntity") (8 . "PLANTS") (62 . 94) (370 . 13) (100 . "AcDbPolyline") (90 . 2) (70 . 0)
(43 . 0.0) (10 3783.073855357 6696.8325791855) (10 3800.9049773756 6696.8325791855))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3782.0513574661 6776.0180995475 0.0) (10 3809.1196263342 6817.6070012748 0.0) (10 3767.8099089681
6797.7349813448 0.0) (10 3763.1975113122 6817.4964932127 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3763.1975113122 6817.4964932127 0.0) (10 3765.396626957 6851.9098512686 0.0) (10 3805.5897966069
6866.1118229981 0.0) (10 3834.8416289593 6870.2863122172 0.0))
((0 . "LWPOLYLINE") (100 . "AcDbEntity") (8 . "PLANTS") (62 . 94) (370 . 13) (100 . "AcDbPolyline") (90 . 2) (70 . 0)
(43 . 0.0) (10 3797.1338235294 6734.5397058824) (10 3779.6346696791 6730.6512383511))
((0 . "LWPOLYLINE") (100 . "AcDbEntity") (8 . "PLANTS") (62 . 94) (370 . 13) (100 . "AcDbPolyline") (90 . 2) (70 . 0)
(43 . 0.0) (10 3766.9683257919 7104.07239819) (10 3770.7391402715 7138.0090497738))
((0 . "LWPOLYLINE") (100 . "AcDbEntity") (8 . "PLANTS") (62 . 94) (370 . 13) (100 . "AcDbPolyline") (90 . 3) (70 . 0)
(43 . 0.0) (10 3812.2171945701 343.1363122172) (10 3789.592760181 348.1123303167) (10 3766.9683257919 369.5333710407))
((0 . "LWPOLYLINE") (100 . "AcDbEntity") (8 . "PLANTS") (62 . 94) (370 . 13) (100 . "AcDbPolyline") (90 . 2) (70 . 0)
(43 . 0.0) (10 3793.3639140271 6776.0180995475) (10 3782.0513574661 6776.0180995475))
((0 . "LWPOLYLINE") (100 . "AcDbEntity") (8 . "PLANTS") (62 . 94) (370 . 13) (100 . "AcDbPolyline") (90 . 2) (70 . 0)
(43 . 0.0) (10 3785.8216063348 6911.7647058824) (10 3834.8416289593 6911.7647058824))
((0 . "LWPOLYLINE") (100 . "AcDbEntity") (8 . "PLANTS") (62 . 94) (370 . 13) (100 . "AcDbPolyline") (90 . 2) (70 . 0)
(43 . 0.0) (10 3793.3639140271 6957.0135746606) (10 3812.2171945701 6960.7840497738))
((0 . "LWPOLYLINE") (100 . "AcDbEntity") (8 . "PLANTS") (62 . 94) (370 . 13) (100 . "AcDbPolyline") (90 . 2) (70 . 0)
(43 . 0.0) (10 3797.1338235294 6734.5397058824) (10 3793.3639140271 6776.0180995475))
((0 . "LWPOLYLINE") (100 . "AcDbEntity") (8 . "PLANTS") (62 . 94) (370 . 13) (100 . "AcDbPolyline") (90 . 2) (70 . 0)
(43 . 0.0) (10 3793.3639140271 6776.0180995475) (10 3831.0704751131 6779.7885746606))
((0 . "LWPOLYLINE") (100 . "AcDbEntity") (8 . "PLANTS") (62 . 94) (370 . 13) (100 . "AcDbPolyline") (90 . 3) (70 . 0)
(43 . 0.0) (10 3815.9883484163 384.6153846154) (10 3805.731561086 388.5404977376) (10 3793.3639140271 426.0944570136))
((0 . "LWPOLYLINE") (100 . "AcDbEntity") (8 . "PLANTS") (62 . 94) (370 . 13) (100 . "AcDbPolyline") (90 . 3) (70 . 0)
(43 . 0.0) (10 3804.6761312217 444.9462669683) (10 3803.4713800905 433.6416289593) (10 3793.3639140271 426.0944570136))
((0 . "LWPOLYLINE") (100 . "AcDbEntity") (8 . "PLANTS") (62 . 94) (370 . 13) (100 . "AcDbPolyline") (90 . 2) (70 . 0)
(43 . 0.0) (10 3797.1338235294 6734.5397058824) (10 3804.6761312217 6734.5397058824))
((0 . "LWPOLYLINE") (100 . "AcDbEntity") (8 . "PLANTS") (62 . 94) (370 . 13) (100 . "AcDbPolyline") (90 . 2) (70 . 0)
(43 . 0.0) (10 3823.5294117647 6693.0621040724) (10 3800.9049773756 6696.8325791855))
((0 . "LWPOLYLINE") (100 . "AcDbEntity") (8 . "PLANTS") (62 . 94) (370 . 13) (100 . "AcDbPolyline") (90 . 2) (70 . 0)
(43 . 0.0) (10 3804.6761312217 6734.5397058824) (10 3800.9049773756 6696.8325791855))
((0 . "LWPOLYLINE") (100 . "AcDbEntity") (8 . "PLANTS") (62 . 94) (370 . 13) (100 . "AcDbPolyline") (90 . 2) (70 . 0)
(43 . 0.0) (10 3951.7349547511 3797.1338235294) (10 3938.6361843624 3794.9511754195))
((0 . "LWPOLYLINE") (100 . "AcDbEntity") (8 . "PLANTS") (62 . 94) (370 . 13) (100 . "AcDbPolyline") (90 . 3) (70 . 0)
(43 . 0.0) (10 3965.5695701357 588.2415158371) (10 3981.9004524887 588.2415158371) (10 3990.9472391618 592.7624213073))
((0 . "LWPOLYLINE") (100 . "AcDbEntity") (8 . "PLANTS") (62 . 94) (370 . 13) (100 . "AcDbPolyline") (90 . 2) (70 . 0)
(43 . 0.0) (10 3823.5294117647 6738.3109728507) (10 3804.6761312217 6734.5397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3859.3510180996 250.7550904977 0.0) (10 3848.4068823605 233.7378944306 0.0) (10 3821.8497693682
226.2433853016 0.0) (10 3804.6761312217 237.556561086 0.0))
((0 . "LWPOLYLINE") (100 . "AcDbEntity") (8 . "PLANTS") (62 . 94) (370 . 13) (100 . "AcDbPolyline") (90 . 3) (70 . 0)
(43 . 0.0) (10 3804.6761312217 237.556561086) (10 3804.8239819005 260.1809954751) (10 3812.2171945701 279.0356334842))
((0 . "LWPOLYLINE") (100 . "AcDbEntity") (8 . "PLANTS") (62 . 94) (370 . 13) (100 . "AcDbPolyline") (90 . 2) (70 . 0)
(43 . 0.0) (10 3819.7582579186 7073.9062217195) (10 3812.2171945701 7062.5940045249))
((0 . "LWPOLYLINE") (100 . "AcDbEntity") (8 . "PLANTS") (62 . 94) (370 . 13) (100 . "AcDbPolyline") (90 . 3) (70 . 0)
(43 . 0.0) (10 3838.6127828054 6941.9308823529) (10 3819.765158371 6959.5797511312) (10 3812.2171945701
6960.7840497738))
((0 . "LWPOLYLINE") (100 . "AcDbEntity") (8 . "PLANTS") (62 . 94) (370 . 13) (100 . "AcDbPolyline") (90 . 2) (70 . 0)
(43 . 0.0) (10 3815.9883484163 324.2845022624) (10 3812.2171945701 343.1363122172))
((0 . "LWPOLYLINE") (100 . "AcDbEntity") (8 . "PLANTS") (62 . 94) (370 . 13) (100 . "AcDbPolyline") (90 . 2) (70 . 0)
(43 . 0.0) (10 3812.2171945701 343.1363122172) (10 3815.9883484163 384.6153846154))
((0 . "LWPOLYLINE") (100 . "AcDbEntity") (8 . "PLANTS") (62 . 94) (370 . 13) (100 . "AcDbPolyline") (90 . 2) (70 . 0)
(43 . 0.0) (10 3812.2171945701 279.0356334842) (10 3812.2171945701 297.8874434389))
((0 . "LWPOLYLINE") (100 . "AcDbEntity") (8 . "PLANTS") (62 . 94) (370 . 13) (100 . "AcDbPolyline") (90 . 2) (70 . 0)
(43 . 0.0) (10 3815.9883484163 324.2845022624) (10 3812.2171945701 297.8874434389))
((0 . "LWPOLYLINE") (100 . "AcDbEntity") (8 . "PLANTS") (62 . 94) (370 . 13) (100 . "AcDbPolyline") (90 . 3) (70 . 0)
(43 . 0.0) (10 3859.3510180995 250.7550904977) (10 3842.234841629 270.2883484163) (10 3812.2171945701 279.0356334842))
((0 . "LWPOLYLINE") (100 . "AcDbEntity") (8 . "PLANTS") (62 . 94) (370 . 13) (100 . "AcDbPolyline") (90 . 3) (70 . 0)
(43 . 0.0) (10 3831.0704751131 422.3218325792) (10 3826.0958144796 388.5404977376) (10 3815.9883484163 384.6153846154))
((0 . "LWPOLYLINE") (100 . "AcDbEntity") (8 . "PLANTS") (62 . 94) (370 . 13) (100 . "AcDbPolyline") (90 . 2) (70 . 0)
(43 . 0.0) (10 3815.9883484163 324.2845022624) (10 3865.0071266968 324.2845022624))
((0 . "LWPOLYLINE") (100 . "AcDbEntity") (8 . "PLANTS") (62 . 94) (370 . 13) (100 . "AcDbPolyline") (90 . 2) (70 . 0)
(43 . 0.0) (10 3827.3005656109 7039.9695701357) (10 3823.5294117647 7051.2817873303))
((0 . "LWPOLYLINE") (100 . "AcDbEntity") (8 . "PLANTS") (62 . 94) (370 . 13) (100 . "AcDbPolyline") (90 . 2) (70 . 0)
(43 . 0.0) (10 3831.0704751131 6779.7885746606) (10 3861.2372171946 6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3842.3826923077 6866.5158371041 0.0) (10 3871.8785719662 6833.2349753933 0.0) (10 3813.134494017
6808.8676175264 0.0) (10 3831.0704751131 6779.7885746606 0.0))
((0 . "LWPOLYLINE") (100 . "AcDbEntity") (8 . "PLANTS") (62 . 94) (370 . 13) (100 . "AcDbPolyline") (90 . 2) (70 . 0)
(43 . 0.0) (10 3834.8416289593 6911.7647058824) (10 3834.8416289593 6870.2863122172))
((0 . "LWPOLYLINE") (100 . "AcDbEntity") (8 . "PLANTS") (62 . 94) (370 . 13) (100 . "AcDbPolyline") (90 . 2) (70 . 0)
(43 . 0.0) (10 3838.6127828054 6919.3064479638) (10 3834.8416289593 6911.7647058824))
((0 . "LWPOLYLINE") (100 . "AcDbEntity") (8 . "PLANTS") (62 . 94) (370 . 13) (100 . "AcDbPolyline") (90 . 2) (70 . 0)
(43 . 0.0) (10 3842.3826923077 6866.5158371041) (10 3834.8416289593 6870.2863122172))
((0 . "LWPOLYLINE") (100 . "AcDbEntity") (8 . "PLANTS") (62 . 94) (370 . 13) (100 . "AcDbPolyline") (90 . 2) (70 . 0)
(43 . 0.0) (10 3838.6127828054 6919.3064479638) (10 3838.6127828054 6941.9308823529))
((0 . "LWPOLYLINE") (100 . "AcDbEntity") (8 . "PLANTS") (62 . 94) (370 . 13) (100 . "AcDbPolyline") (90 . 2) (70 . 0)
(43 . 0.0) (10 3838.6127828054 6941.9308823529) (10 3849.925 6949.4718325792))
((0 . "LWPOLYLINE") (100 . "AcDbEntity") (8 . "PLANTS") (62 . 94) (370 . 13) (100 . "AcDbPolyline") (90 . 3) (70 . 0)
(43 . 0.0) (10 3838.6127828054 6919.3064479638) (10 3849.925 6915.6834841629) (10 3898.9437782805 6915.5351809955))
((0 . "LWPOLYLINE") (100 . "AcDbEntity") (8 . "PLANTS") (62 . 94) (370 . 13) (100 . "AcDbPolyline") (90 . 2) (70 . 0)
(43 . 0.0) (10 3842.3826923077 6866.5158371041) (10 3902.7149321267 6874.0575791855))
((0 . "LWPOLYLINE") (100 . "AcDbEntity") (8 . "PLANTS") (62 . 94) (370 . 13) (100 . "AcDbPolyline") (90 . 2) (70 . 0)
(43 . 0.0) (10 3849.925 441.1764705882) (10 3842.3826923077 437.4066742081))
((0 . "LWPOLYLINE") (100 . "AcDbEntity") (8 . "PLANTS") (62 . 94) (370 . 13) (100 . "AcDbPolyline") (90 . 3) (70 . 0)
(43 . 0.0) (10 3849.925 7021.1164027149) (10 3857.4660633484 6987.1797511312) (10 3849.925 6949.4718325792))
((0 . "LWPOLYLINE") (100 . "AcDbEntity") (8 . "PLANTS") (62 . 94) (370 . 13) (100 . "AcDbPolyline") (90 . 3) (70 . 0)
(43 . 0.0) (10 3900.8299773756 6957.0135746606) (10 3880.0904977376 6956.8652714932) (10 3849.925 6949.4718325792))
((0 . "LWPOLYLINE") (100 . "AcDbEntity") (8 . "PLANTS") (62 . 94) (370 . 13) (100 . "AcDbPolyline") (90 . 3) (70 . 0)
(43 . 0.0) (10 3849.925 441.1764705882) (10 3856.268438914 433.6291855204) (10 3857.4660633484 418.5520361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3849.925 441.1764705882 0.0) (10 3848.8414755861 457.1522685186 0.0) (10 3857.4628150554 493.5069770812
0.0) (10 3880.0904977376 482.6555429865 0.0))
((0 . "LWPOLYLINE") (100 . "AcDbEntity") (8 . "PLANTS") (62 . 94) (370 . 13) (100 . "AcDbPolyline") (90 . 3) (70 . 0)
(43 . 0.0) (10 3853.6949095023 6726.9987556561) (10 3861.243438914 6730.6209276018) (10 3883.8616515837
6730.7692307692))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3883.8616515837 6730.7692307692 0.0) (10 3885.8291644326 6715.3742616656 0.0) (10 3872.8596017531
6696.4834356833 0.0) (10 3853.6949095023 6704.374321267 0.0))
((0 . "LWPOLYLINE") (100 . "AcDbEntity") (8 . "PLANTS") (62 . 94) (370 . 13) (100 . "AcDbPolyline") (90 . 3) (70 . 0)
(43 . 0.0) (10 3859.3510180995 250.7550904977) (10 3887.631561086 237.7049773756) (10 3932.8804298643 237.556561086))
((0 . "LWPOLYLINE") (100 . "AcDbEntity") (8 . "PLANTS") (62 . 94) (370 . 13) (100 . "AcDbPolyline") (90 . 3) (70 . 0)
(43 . 0.0) (10 3859.3510180995 250.7550904977) (10 3878.8859728507 271.4932126697) (10 3880.0904977376 286.5752262443))
((0 . "LWPOLYLINE") (100 . "AcDbEntity") (8 . "PLANTS") (62 . 94) (370 . 13) (100 . "AcDbPolyline") (90 . 2) (70 . 0)
(43 . 0.0) (10 3861.2372171946 6779.7885746606) (10 3861.2372171946 6813.7252262443))
((0 . "LWPOLYLINE") (100 . "AcDbEntity") (8 . "PLANTS") (62 . 94) (370 . 13) (100 . "AcDbPolyline") (90 . 2) (70 . 0)
(43 . 0.0) (10 3902.7149321267 6776.0180995475) (10 3861.2372171946 6779.7885746606))
((0 . "LWPOLYLINE") (100 . "AcDbEntity") (8 . "PLANTS") (62 . 94) (370 . 13) (100 . "AcDbPolyline") (90 . 2) (70 . 0)
(43 . 0.0) (10 3872.5494343891 6553.5442307692) (10 3861.2372171946 6557.3154977376))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3865.0071266969 7055.0530542987 0.0) (10 3866.3298329289 7076.5962008193 0.0) (10 3844.790235343
7109.8965414442 0.0) (10 3876.3193438915 7122.9263574661 0.0))
((0 . "LWPOLYLINE") (100 . "AcDbEntity") (8 . "PLANTS") (62 . 94) (370 . 13) (100 . "AcDbPolyline") (90 . 3) (70 . 0)
(43 . 0.0) (10 3865.0071266968 6410.2563348416) (10 3871.492760181 6421.5688914027) (10 3872.5494343891 6440.42239819))
((0 . "LWPOLYLINE") (100 . "AcDbEntity") (8 . "PLANTS") (62 . 94) (370 . 13) (100 . "AcDbPolyline") (90 . 2) (70 . 0)
(43 . 0.0) (10 3865.0071266968 324.2845022624) (10 3880.0904977376 286.5752262443))
((0 . "LWPOLYLINE") (100 . "AcDbEntity") (8 . "PLANTS") (62 . 94) (370 . 13) (100 . "AcDbPolyline") (90 . 3) (70 . 0)
(43 . 0.0) (10 3865.0071266968 324.2845022624) (10 3872.5494343891 335.596719457) (10 3876.3193438914 335.596719457))
((0 . "LWPOLYLINE") (100 . "AcDbEntity") (8 . "PLANTS") (62 . 94) (370 . 13) (100 . "AcDbPolyline") (90 . 3) (70 . 0)
(43 . 0.0) (10 3880.0904977376 6644.0419683258) (10 3880.0904977376 6647.8132352941) (10 3868.778280543
6655.3541855204))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4920156717) (40
. 1) (40 . 1) (40 . 1) (40 . 1) (10 3880.0904977376 6644.0419683259 0.0) (10 3883.4727125231 6623.0794995502 0.0) (10
3845.4323248452 6615.3352711018 0.0) (10 3844.7697650275 6657.2709441008 0.0) (10 3868.778280543 6655.3541855204 0.0))
((0 . "LWPOLYLINE") (100 . "AcDbEntity") (8 . "PLANTS") (62 . 94) (370 . 13) (100 . "AcDbPolyline") (90 . 2) (70 . 0)
(43 . 0.0) (10 3872.5494343891 6662.8959276018) (10 3868.778280543 6655.3541855204))
((0 . "LWPOLYLINE") (100 . "AcDbEntity") (8 . "PLANTS") (62 . 94) (370 . 13) (100 . "AcDbPolyline") (90 . 3) (70 . 0)
(43 . 0.0) (10 3872.5494343891 6553.5442307692) (10 3873.753280543 6546.003280543) (10 3883.8616515837 6538.4615384615))
((0 . "LWPOLYLINE") (100 . "AcDbEntity") (8 . "PLANTS") (62 . 94) (370 . 13) (100 . "AcDbPolyline") (90 . 3) (70 . 0)
(43 . 0.0) (10 3895.1738687783 6579.9399321267) (10 3876.474321267 6568.6211538462) (10 3872.5494343891
6553.5442307692))
((0 . "LWPOLYLINE") (100 . "AcDbEntity") (8 . "PLANTS") (62 . 94) (370 . 13) (100 . "AcDbPolyline") (90 . 2) (70 . 0)
(43 . 0.0) (10 3876.3193438914 335.596719457) (10 3917.7983031674 328.0542986425))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3876.3193438914 335.596719457 0.0) (10 3876.4907489982 360.5570323603 0.0) (10 3871.9885879023
393.1209973543 0.0) (10 3895.1738687783 411.0096153846 0.0))
((0 . "LWPOLYLINE") (100 . "AcDbEntity") (8 . "PLANTS") (62 . 94) (370 . 13) (100 . "AcDbPolyline") (90 . 2) (70 . 0)
(43 . 0.0) (10 3880.0904977376 6644.0419683258) (10 3891.4027149321 6647.8132352941))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3932.8804298643 237.556561086 0.0) (10 3927.9167978798 262.0278194174 0.0) (10 3906.2918344757
286.254520218 0.0) (10 3880.0904977376 286.5752262443 0.0))
((0 . "LWPOLYLINE") (100 . "AcDbEntity") (8 . "PLANTS") (62 . 94) (370 . 13) (100 . "AcDbPolyline") (90 . 2) (70 . 0)
(43 . 0.0) (10 3932.8804298643 7062.5940045249) (10 3883.8616515837 7013.5746606335))
((0 . "LWPOLYLINE") (100 . "AcDbEntity") (8 . "PLANTS") (62 . 94) (370 . 13) (100 . "AcDbPolyline") (90 . 2) (70 . 0)
(43 . 0.0) (10 3895.1738687783 6730.7692307692) (10 3883.8616515837 6730.7692307692))
((0 . "LWPOLYLINE") (100 . "AcDbEntity") (8 . "PLANTS") (62 . 94) (370 . 13) (100 . "AcDbPolyline") (90 . 3) (70 . 0)
(43 . 0.0) (10 3883.8616515837 6523.3788461538) (10 3880.0904977376 6527.149321267) (10 3883.8616515837
6538.4615384615))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3883.8616515837 6538.4615384615 0.0) (10 3901.8282318417 6538.1036545387 0.0) (10 3916.5965986069
6558.1152197386 0.0) (10 3906.4860859729 6576.1686651584 0.0))
((0 . "LWPOLYLINE") (100 . "AcDbEntity") (8 . "PLANTS") (62 . 94) (370 . 13) (100 . "AcDbPolyline") (90 . 3) (70 . 0)
(43 . 0.0) (10 3891.4027149321 6828.8087104072) (10 3899.0987556561 6809.9547511312) (10 3914.0271493213
6798.6425339367))
((0 . "LWPOLYLINE") (100 . "AcDbEntity") (8 . "PLANTS") (62 . 94) (370 . 13) (100 . "AcDbPolyline") (90 . 2) (70 . 0)
(43 . 0.0) (10 3895.1738687783 6730.7692307692) (10 3917.7983031674 6726.9987556561))
((0 . "LWPOLYLINE") (100 . "AcDbEntity") (8 . "PLANTS") (62 . 94) (370 . 13) (100 . "AcDbPolyline") (90 . 3) (70 . 0)
(43 . 0.0) (10 3895.1738687783 6730.7692307692) (10 3895.321719457 6757.1641402715) (10 3902.7149321267
6776.0180995475))
((0 . "LWPOLYLINE") (100 . "AcDbEntity") (8 . "PLANTS") (62 . 94) (370 . 13) (100 . "AcDbPolyline") (90 . 2) (70 . 0)
(43 . 0.0) (10 3895.1738687783 6579.9399321267) (10 3906.4860859729 6576.1686651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3895.1738687783 6579.9399321267 0.0) (10 3899.5763682774 6593.1559448931 0.0) (10 3903.1341896469
6611.8182695478 0.0) (10 3917.7983031674 6617.6470588235 0.0))
((0 . "LWPOLYLINE") (100 . "AcDbEntity") (8 . "PLANTS") (62 . 94) (370 . 13) (100 . "AcDbPolyline") (90 . 2) (70 . 0)
(43 . 0.0) (10 3895.1738687783 6293.3635746606) (10 3914.0271493213 6300.9049773756))
((0 . "LWPOLYLINE") (100 . "AcDbEntity") (8 . "PLANTS") (62 . 94) (370 . 13) (100 . "AcDbPolyline") (90 . 2) (70 . 0)
(43 . 0.0) (10 3929.110520362 395.92760181) (10 3895.1738687783 411.0096153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3929.110520362 441.1764705882 0.0) (10 3902.6822071171 459.9886395515 0.0) (10 3886.8504038583
429.2445836742 0.0) (10 3895.1738687783 411.0096153846 0.0))
((0 . "LWPOLYLINE") (100 . "AcDbEntity") (8 . "PLANTS") (62 . 94) (370 . 13) (100 . "AcDbPolyline") (90 . 2) (70 . 0)
(43 . 0.0) (10 3898.9437782805 6915.5351809955) (10 3902.7149321267 6907.9942307692))
((0 . "LWPOLYLINE") (100 . "AcDbEntity") (8 . "PLANTS") (62 . 94) (370 . 13) (100 . "AcDbPolyline") (90 . 2) (70 . 0)
(43 . 0.0) (10 3898.9437782805 6915.5351809955) (10 3900.8299773756 6957.0135746606))
((0 . "LWPOLYLINE") (100 . "AcDbEntity") (8 . "PLANTS") (62 . 94) (370 . 13) (100 . "AcDbPolyline") (90 . 2) (70 . 0)
(43 . 0.0) (10 3900.8299773756 6957.0135746606) (10 3925.3393665158 6957.0135746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3900.8299773756 6957.0135746606 0.0) (10 3895.9661318748 6990.4925026674 0.0) (10 3939.7826669187
6996.2617631507 0.0) (10 3947.963800905 7024.8868778281 0.0))
((0 . "LWPOLYLINE") (100 . "AcDbEntity") (8 . "PLANTS") (62 . 94) (370 . 13) (100 . "AcDbPolyline") (90 . 2) (70 . 0)
(43 . 0.0) (10 3902.7149321267 6874.0575791855) (10 3902.7149321267 6907.9942307692))
((0 . "LWPOLYLINE") (100 . "AcDbEntity") (8 . "PLANTS") (62 . 94) (370 . 13) (100 . "AcDbPolyline") (90 . 3) (70 . 0)
(43 . 0.0) (10 3936.6515837104 6934.3891402715) (10 3928.9621040724 6919.460520362) (10 3902.7149321267
6907.9942307692))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3942.3076923077 6857.0892533937 0.0) (10 3934.2768631327 6875.1920906805 0.0) (10 3907.4924322807
6855.5573032634 0.0) (10 3902.7149321267 6874.0575791855 0.0))
((0 . "LWPOLYLINE") (100 . "AcDbEntity") (8 . "PLANTS") (62 . 94) (370 . 13) (100 . "AcDbPolyline") (90 . 2) (70 . 0)
(43 . 0.0) (10 3915.9121040724 6777.9037330317) (10 3902.7149321267 6776.0180995475))
((0 . "LWPOLYLINE") (100 . "AcDbEntity") (8 . "PLANTS") (62 . 94) (370 . 13) (100 . "AcDbPolyline") (90 . 2) (70 . 0)
(43 . 0.0) (10 3915.9121040724 6355.5807692308) (10 3902.7149321267 6349.9246606335))
((0 . "LWPOLYLINE") (100 . "AcDbEntity") (8 . "PLANTS") (62 . 94) (370 . 13) (100 . "AcDbPolyline") (90 . 2) (70 . 0)
(43 . 0.0) (10 3932.8804298643 6579.9399321267) (10 3906.4860859729 6576.1686651584))
((0 . "LWPOLYLINE") (100 . "AcDbEntity") (8 . "PLANTS") (62 . 94) (370 . 13) (100 . "AcDbPolyline") (90 . 2) (70 . 0)
(43 . 0.0) (10 3915.9121040724 6777.9037330317) (10 3914.0271493213 6798.6425339367))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3942.3076923077 6857.0892533937 0.0) (10 3917.8542316031 6846.1830048795 0.0) (10 3937.1030260651
6811.219965355 0.0) (10 3914.0271493213 6798.6425339367 0.0))
((0 . "LWPOLYLINE") (100 . "AcDbEntity") (8 . "PLANTS") (62 . 94) (370 . 13) (100 . "AcDbPolyline") (90 . 2) (70 . 0)
(43 . 0.0) (10 3914.0271493213 6478.129638009) (10 3921.5682126697 6478.129638009))
((0 . "LWPOLYLINE") (100 . "AcDbEntity") (8 . "PLANTS") (62 . 94) (370 . 13) (100 . "AcDbPolyline") (90 . 2) (70 . 0)
(43 . 0.0) (10 3914.0271493213 6478.129638009) (10 3917.7983031674 6512.0662895928))
((0 . "LWPOLYLINE") (100 . "AcDbEntity") (8 . "PLANTS") (62 . 94) (370 . 13) (100 . "AcDbPolyline") (90 . 3) (70 . 0)
(43 . 0.0) (10 3921.5682126697 6278.2805429864) (10 3923.9874434389 6289.592760181) (10 3914.0271493213
6300.9049773756))
((0 . "LWPOLYLINE") (100 . "AcDbEntity") (8 . "PLANTS") (62 . 94) (370 . 13) (100 . "AcDbPolyline") (90 . 3) (70 . 0)
(43 . 0.0) (10 3915.9121040724 6355.5807692308) (10 3917.7914027149 6323.5294117647) (10 3914.0271493213
6300.9049773756))
((0 . "LWPOLYLINE") (100 . "AcDbEntity") (8 . "PLANTS") (62 . 94) (370 . 13) (100 . "AcDbPolyline") (90 . 2) (70 . 0)
(43 . 0.0) (10 3914.0271493213 6248.1147058824) (10 3917.7983031674 6206.6364253394))
((0 . "LWPOLYLINE") (100 . "AcDbEntity") (8 . "PLANTS") (62 . 94) (370 . 13) (100 . "AcDbPolyline") (90 . 3) (70 . 0)
(43 . 0.0) (10 3915.9121040724 6777.9037330317) (10 3927.90260181 6764.7089366516) (10 3929.110520362 6734.5397058824))
((0 . "LWPOLYLINE") (100 . "AcDbEntity") (8 . "PLANTS") (62 . 94) (370 . 13) (100 . "AcDbPolyline") (90 . 2) (70 . 0)
(43 . 0.0) (10 3915.9121040724 6777.9037330317) (10 3970.5882352941 6779.7885746606))
((0 . "LWPOLYLINE") (100 . "AcDbEntity") (8 . "PLANTS") (62 . 94) (370 . 13) (100 . "AcDbPolyline") (90 . 2) (70 . 0)
(43 . 0.0) (10 3915.9121040724 6355.5807692308) (10 3936.6515837104 6353.6952488688))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3915.9121040725 6355.5807692308 0.0) (10 3919.8557470506 6391.1750830427 0.0) (10 3901.114162718
6428.804431163 0.0) (10 3921.5682126697 6463.0468325792 0.0))
((0 . "LWPOLYLINE") (100 . "AcDbEntity") (8 . "PLANTS") (62 . 94) (370 . 13) (100 . "AcDbPolyline") (90 . 3) (70 . 0)
(43 . 0.0) (10 3917.7983031674 6726.9987556561) (10 3917.9461538462 6700.6099547511) (10 3921.5682126697
6693.0621040724))
((0 . "LWPOLYLINE") (100 . "AcDbEntity") (8 . "PLANTS") (62 . 94) (370 . 13) (100 . "AcDbPolyline") (90 . 2) (70 . 0)
(43 . 0.0) (10 3917.7983031674 6726.9987556561) (10 3929.110520362 6734.5397058824))
((0 . "LWPOLYLINE") (100 . "AcDbEntity") (8 . "PLANTS") (62 . 94) (370 . 13) (100 . "AcDbPolyline") (90 . 3) (70 . 0)
(43 . 0.0) (10 3932.8804298643 6579.9399321267) (10 3924.1417420814 6610.0987556561) (10 3917.7983031674
6617.6470588235))
((0 . "LWPOLYLINE") (100 . "AcDbEntity") (8 . "PLANTS") (62 . 94) (370 . 13) (100 . "AcDbPolyline") (90 . 2) (70 . 0)
(43 . 0.0) (10 3917.7983031674 6617.6470588235) (10 3925.3393665158 6636.5010180995))
((0 . "LWPOLYLINE") (100 . "AcDbEntity") (8 . "PLANTS") (62 . 94) (370 . 13) (100 . "AcDbPolyline") (90 . 2) (70 . 0)
(43 . 0.0) (10 3921.5682126697 320.5118778281) (10 3917.7983031674 328.0542986425))
((0 . "LWPOLYLINE") (100 . "AcDbEntity") (8 . "PLANTS") (62 . 94) (370 . 13) (100 . "AcDbPolyline") (90 . 2) (70 . 0)
(43 . 0.0) (10 3917.7983031674 328.0542986425) (10 3947.963800905 339.3665158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3925.3393665158 6636.5010180995 0.0) (10 3915.7866017255 6651.6175407114 0.0) (10 3907.1080921668
6677.4015270214 0.0) (10 3921.5682126697 6693.0621040724 0.0))
((0 . "LWPOLYLINE") (100 . "AcDbEntity") (8 . "PLANTS") (62 . 94) (370 . 13) (100 . "AcDbPolyline") (90 . 3) (70 . 0)
(43 . 0.0) (10 3951.7349547511 6726.9987556561) (10 3946.7596153846 6704.5221719457) (10 3921.5682126697
6693.0621040724))
((0 . "LWPOLYLINE") (100 . "AcDbEntity") (8 . "PLANTS") (62 . 94) (370 . 13) (100 . "AcDbPolyline") (90 . 2) (70 . 0)
(43 . 0.0) (10 3921.5682126697 6478.129638009) (10 3921.5682126697 6463.0468325792))
((0 . "LWPOLYLINE") (100 . "AcDbEntity") (8 . "PLANTS") (62 . 94) (370 . 13) (100 . "AcDbPolyline") (90 . 2) (70 . 0)
(43 . 0.0) (10 3947.963800905 6481.9004524887) (10 3921.5682126697 6478.129638009))
((0 . "LWPOLYLINE") (100 . "AcDbEntity") (8 . "PLANTS") (62 . 94) (370 . 13) (100 . "AcDbPolyline") (90 . 3) (70 . 0)
(43 . 0.0) (10 3966.817081448 6402.7149321267) (10 3946.9071266968 6440.42239819) (10 3921.5682126697 6463.0468325792))
((0 . "LWPOLYLINE") (100 . "AcDbEntity") (8 . "PLANTS") (62 . 94) (370 . 13) (100 . "AcDbPolyline") (90 . 2) (70 . 0)
(43 . 0.0) (10 3936.6515837104 6934.3891402715) (10 3925.3393665158 6957.0135746606))
((0 . "LWPOLYLINE") (100 . "AcDbEntity") (8 . "PLANTS") (62 . 94) (370 . 13) (100 . "AcDbPolyline") (90 . 2) (70 . 0)
(43 . 0.0) (10 3951.7349547511 6987.1797511312) (10 3925.3393665158 6957.0135746606))
((0 . "LWPOLYLINE") (100 . "AcDbEntity") (8 . "PLANTS") (62 . 94) (370 . 13) (100 . "AcDbPolyline") (90 . 2) (70 . 0)
(43 . 0.0) (10 3959.2760180995 6640.2714932127) (10 3925.3393665158 6636.5010180995))
((0 . "LWPOLYLINE") (100 . "AcDbEntity") (8 . "PLANTS") (62 . 94) (370 . 13) (100 . "AcDbPolyline") (90 . 2) (70 . 0)
(43 . 0.0) (10 3929.110520362 6734.5397058824) (10 3951.7349547511 6726.9987556561))
((0 . "LWPOLYLINE") (100 . "AcDbEntity") (8 . "PLANTS") (62 . 94) (370 . 13) (100 . "AcDbPolyline") (90 . 2) (70 . 0)
(43 . 0.0) (10 3936.6515837104 403.4700226244) (10 3929.110520362 441.1764705882))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3929.110520362 441.1764705882 0.0) (10 3957.8526165158 456.5472831072 0.0) (10 3985.2024893007
413.657645804 0.0) (10 3974.3593891403 388.3851809955 0.0))
((0 . "LWPOLYLINE") (100 . "AcDbEntity") (8 . "PLANTS") (62 . 94) (370 . 13) (100 . "AcDbPolyline") (90 . 3) (70 . 0)
(43 . 0.0) (10 3947.963800905 339.3665158371) (10 3930.3078054299 380.8455882353) (10 3929.110520362 395.92760181))
((0 . "LWPOLYLINE") (100 . "AcDbEntity") (8 . "PLANTS") (62 . 94) (370 . 13) (100 . "AcDbPolyline") (90 . 2) (70 . 0)
(43 . 0.0) (10 3936.6515837104 403.4700226244) (10 3929.110520362 395.92760181))
((0 . "LWPOLYLINE") (100 . "AcDbEntity") (8 . "PLANTS") (62 . 94) (370 . 13) (100 . "AcDbPolyline") (90 . 3) (70 . 0)
(43 . 0.0) (10 3932.8804298643 6579.9399321267) (10 3940.267760181 6572.3916289593) (10 3940.4227375566
6542.2320135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 3932.8804298643 237.556561086 0.0) (10 3955.8354091494 228.3017004966 0.0) (10 3984.570092305
229.1736007325 0.0) (10 4004.5248868778 245.0989819005 0.0))
((0 . "LWPOLYLINE") (100 . "AcDbEntity") (8 . "PLANTS") (62 . 94) (370 . 13) (100 . "AcDbPolyline") (90 . 2) (70 . 0)
(43 . 0.0) (10 3936.6515837104 6934.3891402715) (10 3974.3593891403 6934.3891402715))
((0 . "LWPOLYLINE") (100 . "AcDbEntity") (8 . "PLANTS") (62 . 94) (370 . 13) (100 . "AcDbPolyline") (90 . 3) (70 . 0)
(43 . 0.0) (10 3936.6515837104 403.4700226244) (10 3963.0464932127 389.4423076923) (10 3974.3593891403 388.3851809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4008.296040724 6832.5791855203 0.0) (10 3990.8638265099 6852.2622452366 0.0) (10 3962.6510748172
6846.2954012956 0.0) (10 3942.3076923077 6857.0892533936 0.0))
((0 . "LWPOLYLINE") (100 . "AcDbEntity") (8 . "PLANTS") (62 . 94) (370 . 13) (100 . "AcDbPolyline") (90 . 3) (70 . 0)
(43 . 0.0) (10 3942.3076923077 6857.0892533937) (10 3959.4306561086 6889.1337104072) (10 3981.9004524887
6900.4524886878))
((0 . "LWPOLYLINE") (100 . "AcDbEntity") (8 . "PLANTS") (62 . 94) (370 . 13) (100 . "AcDbPolyline") (90 . 2) (70 . 0)
(43 . 0.0) (10 4000.4985044865 6481.9004524887) (10 3947.963800905 6481.9004524887))
((0 . "LWPOLYLINE") (100 . "AcDbEntity") (8 . "PLANTS") (62 . 94) (370 . 13) (100 . "AcDbPolyline") (90 . 2) (70 . 0)
(43 . 0.0) (10 3947.963800905 6481.9004524887) (10 3951.7349547511 6504.5248868778))
((0 . "LWPOLYLINE") (100 . "AcDbEntity") (8 . "PLANTS") (62 . 94) (370 . 13) (100 . "AcDbPolyline") (90 . 2) (70 . 0)
(43 . 0.0) (10 3989.4415158371 335.596719457) (10 3947.963800905 339.3665158371))
((0 . "LWPOLYLINE") (100 . "AcDbEntity") (8 . "PLANTS") (62 . 94) (370 . 13) (100 . "AcDbPolyline") (90 . 2) (70 . 0)
(43 . 0.0) (10 3974.3593891403 6726.9987556561) (10 3951.7349547511 6726.9987556561))
((0 . "LWPOLYLINE") (100 . "AcDbEntity") (8 . "PLANTS") (62 . 94) (370 . 13) (100 . "AcDbPolyline") (90 . 3) (70 . 0)
(43 . 0.0) (10 3951.7349547511 3797.1338235294) (10 3989.4415158371 3796.9859728507) (10 4000.7537330317
3793.3639140271))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4038.4615384616 3883.8616515837 0.0) (10 4031.695955041 3836.7153933562 0.0) (10 3948.2645301867
3852.786185258 0.0) (10 3951.7349547511 3797.1338235293 0.0))
((0 . "LWPOLYLINE") (100 . "AcDbEntity") (8 . "PLANTS") (62 . 94) (370 . 13) (100 . "AcDbPolyline") (90 . 2) (70 . 0)
(43 . 0.0) (10 3985.6716063348 6587.4808823529) (10 3959.2760180995 6640.2714932127))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4000.7537330317 6696.8325791855 0.0) (10 3955.7499934207 6697.5047530557 0.0) (10 3989.4142914674
6653.3344214373 0.0) (10 3959.2760180995 6640.2714932127 0.0))
((0 . "LWPOLYLINE") (100 . "AcDbEntity") (8 . "PLANTS") (62 . 94) (370 . 13) (100 . "AcDbPolyline") (90 . 3) (70 . 0)
(43 . 0.0) (10 3963.0471719457 7055.0530542986) (10 3964.10260181 7066.3652714932) (10 3974.3593891403 7085.218438914))
((0 . "LWPOLYLINE") (100 . "AcDbEntity") (8 . "PLANTS") (62 . 94) (370 . 13) (100 . "AcDbPolyline") (90 . 3) (70 . 0)
(43 . 0.0) (10 3970.5882352941 6779.7885746606) (10 3970.440158371 6798.6425339367) (10 3963.0471719457
6817.4964932127))
((0 . "LWPOLYLINE") (100 . "AcDbEntity") (8 . "PLANTS") (62 . 94) (370 . 13) (100 . "AcDbPolyline") (90 . 3) (70 . 0)
(43 . 0.0) (10 4008.296040724 6753.3936651584) (10 3993.2126696833 6758.3618778281) (10 3970.5882352941
6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4032.8054298643 461.9145927602 0.0) (10 4008.8113270377 449.6408505008 0.0) (10 3992.7500324331
476.1572927155 0.0) (10 3970.5882352941 471.3433257919 0.0))
((0 . "LWPOLYLINE") (100 . "AcDbEntity") (8 . "PLANTS") (62 . 94) (370 . 13) (100 . "AcDbPolyline") (90 . 2) (70 . 0)
(43 . 0.0) (10 3985.6716063348 6926.84739819) (10 3974.3593891403 6934.3891402715))
((0 . "LWPOLYLINE") (100 . "AcDbEntity") (8 . "PLANTS") (62 . 94) (370 . 13) (100 . "AcDbPolyline") (90 . 2) (70 . 0)
(43 . 0.0) (10 3974.3593891403 6934.3891402715) (10 3989.4415158371 6998.4919683258))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4038.4615384616 3883.8616515837 0.0) (10 4034.6102467945 3910.2726017467 0.0) (10 3991.0967721852
3896.0014733824 0.0) (10 3974.3593891403 3887.631561086 0.0))
((0 . "LWPOLYLINE") (100 . "AcDbEntity") (8 . "PLANTS") (62 . 94) (370 . 13) (100 . "AcDbPolyline") (90 . 2) (70 . 0)
(43 . 0.0) (10 3974.3593891403 3763.1971719457) (10 3996.9838235294 3770.739479638))
((0 . "LWPOLYLINE") (100 . "AcDbEntity") (8 . "PLANTS") (62 . 94) (370 . 13) (100 . "AcDbPolyline") (90 . 2) (70 . 0)
(43 . 0.0) (10 3974.3593891403 388.3851809955) (10 3989.4415158371 346.9089366516))
((0 . "LWPOLYLINE") (100 . "AcDbEntity") (8 . "PLANTS") (62 . 94) (370 . 13) (100 . "AcDbPolyline") (90 . 2) (70 . 0)
(43 . 0.0) (10 3989.4415158371 6892.9107466063) (10 3981.9004524887 6900.4524886878))
((0 . "LWPOLYLINE") (100 . "AcDbEntity") (8 . "PLANTS") (62 . 94) (370 . 13) (100 . "AcDbPolyline") (90 . 2) (70 . 0)
(43 . 0.0) (10 3985.6716063348 6926.84739819) (10 3981.9004524887 6900.4524886878))
((0 . "LWPOLYLINE") (100 . "AcDbEntity") (8 . "PLANTS") (62 . 94) (370 . 13) (100 . "AcDbPolyline") (90 . 2) (70 . 0)
(43 . 0.0) (10 3985.6716063348 6926.84739819) (10 4000.7537330317 6926.84739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4049.7737556561 7073.9062217195 0.0) (10 4022.7488204081 7065.7245024445 0.0) (10 3968.1461992425
7033.8128273252 0.0) (10 3989.441515837 6998.4919683258 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4064.8571266968 7043.7408371041 0.0) (10 4050.2920751293 7017.1196638608 0.0) (10 4019.5834266254
6999.3504843211 0.0) (10 3989.4415158371 6998.4919683258 0.0))
((0 . "LWPOLYLINE") (100 . "AcDbEntity") (8 . "PLANTS") (62 . 94) (370 . 13) (100 . "AcDbPolyline") (90 . 2) (70 . 0)
(43 . 0.0) (10 3989.4415158371 335.596719457) (10 3989.4415158371 346.9089366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4030.9204751131 426.0944570136 0.0) (10 3986.8806745341 406.4589252136 0.0) (10 4060.4827165459
346.8576946692 0.0) (10 3989.4415158371 346.9089366516 0.0))
((0 . "LWPOLYLINE") (100 . "AcDbEntity") (8 . "PLANTS") (62 . 94) (370 . 13) (100 . "AcDbPolyline") (90 . 3) (70 . 0)
(43 . 0.0) (10 3989.4415158371 335.596719457) (10 3996.8354072398 316.742081448) (10 4004.5248868778 245.0989819005))
((0 . "LWPOLYLINE") (100 . "AcDbEntity") (8 . "PLANTS") (62 . 94) (370 . 13) (100 . "AcDbPolyline") (90 . 2) (70 . 0)
(43 . 0.0) (10 4006.0791010208 6536.7763184094) (10 3996.9838235294 6546.003280543))
((0 . "LWPOLYLINE") (100 . "AcDbEntity") (8 . "PLANTS") (62 . 94) (370 . 13) (100 . "AcDbPolyline") (90 . 3) (70 . 0)
(43 . 0.0) (10 3996.9838235294 3770.739479638) (10 4008.5159502262 3733.25260181) (10 4008.8728889494 3733.0316742081))
((0 . "LWPOLYLINE") (100 . "AcDbEntity") (8 . "PLANTS") (62 . 94) (370 . 13) (100 . "AcDbPolyline") (90 . 2) (70 . 0)
(43 . 0.0) (10 3996.9838235294 3770.739479638) (10 4000.7537330317 3793.3639140271))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4042.2326923077 6851.4331447964 0.0) (10 4036.7357451202 6879.894950961 0.0) (10 4023.5966425718
6908.2126458201 0.0) (10 4000.7537330317 6926.84739819 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5535187087)
(40 . 0.6856087558) (40 . 1) (40 . 1) (40 . 1) (40 . 1) (10 4211.9159502263 7055.0530542986 0.0) (10 4162.8636661318
7057.5428008426 0.0) (10 4107.3740385899 7032.2091487375 0.0) (10 4043.8552873311 6975.0907803038 0.0) (10
4017.1926092126 6948.234588144 0.0) (10 4000.7537330317 6926.8473981901 0.0))
((0 . "LWPOLYLINE") (100 . "AcDbEntity") (8 . "PLANTS") (62 . 94) (370 . 13) (100 . "AcDbPolyline") (90 . 2) (70 . 0)
(43 . 0.0) (10 4000.7537330317 6696.8325791855) (10 4012.0659502262 6693.0621040724))
((0 . "LWPOLYLINE") (100 . "AcDbEntity") (8 . "PLANTS") (62 . 94) (370 . 13) (100 . "AcDbPolyline") (90 . 2) (70 . 0)
(43 . 0.0) (10 4000.7537330317 6696.8325791855) (10 4008.296040724 6753.3936651584))
((0 . "LWPOLYLINE") (100 . "AcDbEntity") (8 . "PLANTS") (62 . 94) (370 . 13) (100 . "AcDbPolyline") (90 . 2) (70 . 0)
(43 . 0.0) (10 4000.7537330317 3793.3639140271) (10 4019.6082579186 3793.3639140271))
((0 . "LWPOLYLINE") (100 . "AcDbEntity") (8 . "PLANTS") (62 . 94) (370 . 13) (100 . "AcDbPolyline") (90 . 3) (70 . 0)
(43 . 0.0) (10 4053.5449095023 241.3263574661) (10 4015.8371040724 241.4747737557) (10 4004.5248868778 245.0989819005))
((0 . "LWPOLYLINE") (100 . "AcDbEntity") (8 . "PLANTS") (62 . 94) (370 . 13) (100 . "AcDbPolyline") (90 . 3) (70 . 0)
(43 . 0.0) (10 4015.8371040724 6787.3303167421) (10 4008.4438914027 6802.4130090498) (10 4008.296040724
6832.5791855204))
((0 . "LWPOLYLINE") (100 . "AcDbEntity") (8 . "PLANTS") (62 . 94) (370 . 13) (100 . "AcDbPolyline") (90 . 3) (70 . 0)
(43 . 0.0) (10 4008.296040724 6832.5791855204) (10 4023.3781674208 6833.7834841629) (10 4042.2326923077
6851.4331447964))
((0 . "LWPOLYLINE") (100 . "AcDbEntity") (8 . "PLANTS") (62 . 94) (370 . 13) (100 . "AcDbPolyline") (90 . 3) (70 . 0)
(43 . 0.0) (10 4015.8371040724 6787.3303167421) (10 4008.4438914027 6768.4763574661) (10 4008.296040724
6753.3936651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4012.5492447465 6600.3993983784 0.0) (10 4005.2343651943 6613.321000306 0.0) (10 4003.7757646599
6631.2687714551 0.0) (10 4012.0659502262 6644.0419683258 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4459940973) (40
. 1) (40 . 1) (40 . 1) (40 . 1) (10 4015.8371040724 6787.3303167421 0.0) (10 4062.4954977267 6785.3437690992 0.0) (10
4166.6940625502 6784.1321609168 0.0) (10 4271.1734253311 6790.1928118512 0.0) (10 4328.8080316742 6783.559841629 0.0))
((0 . "LWPOLYLINE") (100 . "AcDbEntity") (8 . "PLANTS") (62 . 94) (370 . 13) (100 . "AcDbPolyline") (90 . 3) (70 . 0)
(43 . 0.0) (10 4049.7737556561 3940.4227375566) (10 4030.9204751131 3940.267760181) (10 4019.6082579186
3932.8804298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4076.1693438914 3880.0904977376 0.0) (10 4084.2628367838 3832.2610788096 0.0) (10 4014.9329430425
3840.2567632955 0.0) (10 4019.6082579186 3793.3639140271 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4100.6787330317 3804.6761312217 0.0) (10 4071.4778482657 3814.4237007983 0.0) (10 4048.2467907934
3787.1913332885 0.0) (10 4019.6082579186 3793.3639140271 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4100.6787330317 3804.6761312217 0.0) (10 4096.9143729456 3765.0720306165 0.0) (10 4047.8080386701
3767.4012849449 0.0) (10 4035.9884928372 3733.0316742081 0.0))
((0 . "LWPOLYLINE") (100 . "AcDbEntity") (8 . "PLANTS") (62 . 94) (370 . 13) (100 . "AcDbPolyline") (90 . 2) (70 . 0)
(43 . 0.0) (10 4030.9204751131 426.0944570136) (10 4032.8054298643 461.9145927602))
((0 . "LWPOLYLINE") (100 . "AcDbEntity") (8 . "PLANTS") (62 . 94) (370 . 13) (100 . "AcDbPolyline") (90 . 3) (70 . 0)
(43 . 0.0) (10 4030.9204751131 426.0944570136) (10 4049.7675339367 427.2978506787) (10 4057.3148190045 441.1764705882))
((0 . "LWPOLYLINE") (100 . "AcDbEntity") (8 . "PLANTS") (62 . 94) (370 . 13) (100 . "AcDbPolyline") (90 . 3) (70 . 0)
(43 . 0.0) (10 4032.8054298643 461.9145927602) (10 4049.625678733 452.3409502262) (10 4057.3148190045 441.1764705882))
((0 . "LWPOLYLINE") (100 . "AcDbEntity") (8 . "PLANTS") (62 . 94) (370 . 13) (100 . "AcDbPolyline") (90 . 2) (70 . 0)
(43 . 0.0) (10 4032.8054298643 461.9145927602) (10 4038.4615384615 505.2799773756))
((0 . "LWPOLYLINE") (100 . "AcDbEntity") (8 . "PLANTS") (62 . 94) (370 . 13) (100 . "AcDbPolyline") (90 . 2) (70 . 0)
(43 . 0.0) (10 4038.4615384615 3883.8616515837) (10 4076.1693438914 3880.0904977376))
((0 . "LWPOLYLINE") (100 . "AcDbEntity") (8 . "PLANTS") (62 . 94) (370 . 13) (100 . "AcDbPolyline") (90 . 3) (70 . 0)
(43 . 0.0) (10 4121.4182126697 6847.6618778281) (10 4083.7104072398 6840.2687782805) (10 4042.2326923077
6851.4331447964))
((0 . "LWPOLYLINE") (100 . "AcDbEntity") (8 . "PLANTS") (62 . 94) (370 . 13) (100 . "AcDbPolyline") (90 . 2) (70 . 0)
(43 . 0.0) (10 4049.7737556561 7073.9062217195) (10 4064.8571266968 7043.7408371041))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4551417454) (40
. 1) (40 . 1) (40 . 1) (40 . 1) (10 4049.7737556561 7073.9062217194 0.0) (10 4058.3968951625 7088.1154682215 0.0) (10
4108.0637226223 7106.683402453 0.0) (10 4084.6272861759 7044.7748630129 0.0) (10 4064.8571266968 7043.740837104 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4053.5449095023 4023.3781674208 0.0) (10 4087.6909489705 4045.5188746817 0.0) (10 4091.1807546227
3949.2787304804 0.0) (10 4128.9592760181 3963.0471719457 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4878779689) (40
. 1) (40 . 1) (40 . 1) (40 . 1) (10 4053.5449095022 241.3263574659 0.0) (10 4072.4118998139 226.6547000468 0.0) (10
4122.8662665772 236.8633658056 0.0) (10 4173.0762112053 225.0323689093 0.0) (10 4189.2915158371 248.8687782805 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4053.5449095023 241.3263574661 0.0) (10 4052.001618609 259.3676216959 0.0) (10 4069.2946289943
277.7154565142 0.0) (10 4087.481561086 275.2630090498 0.0))
((0 . "LWPOLYLINE") (100 . "AcDbEntity") (8 . "PLANTS") (62 . 94) (370 . 13) (100 . "AcDbPolyline") (90 . 2) (70 . 0)
(43 . 0.0) (10 4098.7937782805 460.0311085973) (10 4057.3148190045 441.1764705882))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4121.4182126697 369.5333710407 0.0) (10 4109.5258068925 386.6285740198 0.0) (10 4083.843964931
397.0130783742 0.0) (10 4064.8571266968 384.6153846154 0.0))
((0 . "LWPOLYLINE") (100 . "AcDbEntity") (8 . "PLANTS") (62 . 94) (370 . 13) (100 . "AcDbPolyline") (90 . 3) (70 . 0)
(43 . 0.0) (10 4226.9980769231 6734.5397058824) (10 4151.5837104072 6734.3918552036) (10 4132.7304298643
6730.7692307692))
((0 . "LWPOLYLINE") (100 . "AcDbEntity") (8 . "PLANTS") (62 . 94) (370 . 13) (100 . "AcDbPolyline") (90 . 2) (70 . 0)
(43 . 0.0) (10 4132.7304298643 6730.7692307692) (10 4068.6270361991 6734.5397058824))
((0 . "LWPOLYLINE") (100 . "AcDbEntity") (8 . "PLANTS") (62 . 94) (370 . 13) (100 . "AcDbPolyline") (90 . 3) (70 . 0)
(43 . 0.0) (10 4072.3981900452 3936.6515837104) (10 4092.0872171946 3946.5455882353) (10 4121.4182126697
3940.4227375566))
((0 . "LWPOLYLINE") (100 . "AcDbEntity") (8 . "PLANTS") (62 . 94) (370 . 13) (100 . "AcDbPolyline") (90 . 2) (70 . 0)
(43 . 0.0) (10 4121.4182126697 3925.3393665158) (10 4076.1693438914 3880.0904977376))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4087.481561086 275.2630090498 0.0) (10 4082.3340844988 290.0414169614 0.0) (10 4088.6584052988
320.1844653013 0.0) (10 4113.8759049774 309.1996606335 0.0))
((0 . "LWPOLYLINE") (100 . "AcDbEntity") (8 . "PLANTS") (62 . 94) (370 . 13) (100 . "AcDbPolyline") (90 . 2) (70 . 0)
(43 . 0.0) (10 4113.8759049774 279.0356334842) (10 4087.481561086 275.2630090498))
((0 . "LWPOLYLINE") (100 . "AcDbEntity") (8 . "PLANTS") (62 . 94) (370 . 13) (100 . "AcDbPolyline") (90 . 3) (70 . 0)
(43 . 0.0) (10 4136.5003393665 4049.7737556561) (10 4117.6470588235 4060.9313348416) (10 4091.2514705882
4061.0859728507))
((0 . "LWPOLYLINE") (100 . "AcDbEntity") (8 . "PLANTS") (62 . 94) (370 . 13) (100 . "AcDbPolyline") (90 . 2) (70 . 0)
(43 . 0.0) (10 4091.2514705882 3831.0704751131) (10 4102.5636877828 3815.9883484163))
((0 . "LWPOLYLINE") (100 . "AcDbEntity") (8 . "PLANTS") (62 . 94) (370 . 13) (100 . "AcDbPolyline") (90 . 3) (70 . 0)
(43 . 0.0) (10 4095.0226244344 358.2211538462) (10 4106.334841629 355.6609728507) (10 4121.4182126697 369.5333710407))
((0 . "LWPOLYLINE") (100 . "AcDbEntity") (8 . "PLANTS") (62 . 94) (370 . 13) (100 . "AcDbPolyline") (90 . 2) (70 . 0)
(43 . 0.0) (10 4098.7937782805 460.0311085973) (10 4117.6470588235 448.7188914027))
((0 . "LWPOLYLINE") (100 . "AcDbEntity") (8 . "PLANTS") (62 . 94) (370 . 13) (100 . "AcDbPolyline") (90 . 2) (70 . 0)
(43 . 0.0) (10 4098.7937782805 460.0311085973) (10 4102.5636877828 471.3433257919))
((0 . "LWPOLYLINE") (100 . "AcDbEntity") (8 . "PLANTS") (62 . 94) (370 . 13) (100 . "AcDbPolyline") (90 . 3) (70 . 0)
(43 . 0.0) (10 4200.6037330317 3800.9049773756) (10 4117.6470588235 3797.282239819) (10 4100.6787330317
3804.6761312217))
((0 . "LWPOLYLINE") (100 . "AcDbEntity") (8 . "PLANTS") (62 . 94) (370 . 13) (100 . "AcDbPolyline") (90 . 2) (70 . 0)
(43 . 0.0) (10 4100.6787330317 3804.6761312217) (10 4102.5636877828 3815.9883484163))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4102.5636877828 4038.4615384615 0.0) (10 4087.6987592163 4027.0419789114 0.0) (10 4141.6519575995
4006.0886908813 0.0) (10 4132.7304298643 4015.8371040724 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3974712545) (40
. 1) (40 . 1) (40 . 1) (40 . 1) (10 4166.6670814479 3880.0904977376 0.0) (10 4159.0822797829 3868.5210945838 0.0) (10
4164.1837439779 3826.2411428753 0.0) (10 4108.4163754204 3842.1247962051 0.0) (10 4102.5636877828 3815.9883484163 0.0))
((0 . "LWPOLYLINE") (100 . "AcDbEntity") (8 . "PLANTS") (62 . 94) (370 . 13) (100 . "AcDbPolyline") (90 . 2) (70 . 0)
(43 . 0.0) (10 4121.4182126697 3880.0904977376) (10 4113.8759049774 3876.3193438914))
((0 . "LWPOLYLINE") (100 . "AcDbEntity") (8 . "PLANTS") (62 . 94) (370 . 13) (100 . "AcDbPolyline") (90 . 2) (70 . 0)
(43 . 0.0) (10 4113.8759049774 279.0356334842) (10 4113.8759049774 309.1996606335))
((0 . "LWPOLYLINE") (100 . "AcDbEntity") (8 . "PLANTS") (62 . 94) (370 . 13) (100 . "AcDbPolyline") (90 . 2) (70 . 0)
(43 . 0.0) (10 4113.8759049774 309.1996606335) (10 4147.8125565611 312.9722850679))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4113.8759049774 279.0356334841 0.0) (10 4133.1592723158 258.741689341 0.0) (10 4156.2667682827
294.969267414 0.0) (10 4147.8125565611 312.9722850679 0.0))
((0 . "LWPOLYLINE") (100 . "AcDbEntity") (8 . "PLANTS") (62 . 94) (370 . 13) (100 . "AcDbPolyline") (90 . 3) (70 . 0)
(43 . 0.0) (10 4140.2714932127 6994.7207013575) (10 4121.7207013575 6983.2675339367) (10 4121.4182126697
6975.8675339367))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4196.8325791855 6843.8914027149 0.0) (10 4174.5588934569 6829.4743086435 0.0) (10 4143.8386649375
6847.361024387 0.0) (10 4121.4182126697 6847.6618778281 0.0))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.4147333305)
(40 . 0.5080552709) (40 . 0.5924736936) (40 . 1) (40 . 1) (40 . 1) (40 . 1) (10 4121.4182126697 6847.6618778281 0.0) (10
4120.4205328727 6885.2157381002 0.0) (10 4065.964530733 6887.8940186308 0.0) (10 4045.3153512533 6930.9020183151 0.0)
(10 4084.502694703 6951.4831014452 0.0) (10 4128.2524876254 6909.8183238759 0.0) (10 4151.5837104072 6907.9942307692
0.0))
((0 . "LWPOLYLINE") (100 . "AcDbEntity") (8 . "PLANTS") (62 . 94) (370 . 13) (100 . "AcDbPolyline") (90 . 2) (70 . 0)
(43 . 0.0) (10 4121.4182126697 3925.3393665158) (10 4121.4182126697 3940.4227375566))
((0 . "LWPOLYLINE") (100 . "AcDbEntity") (8 . "PLANTS") (62 . 94) (370 . 13) (100 . "AcDbPolyline") (90 . 2) (70 . 0)
(43 . 0.0) (10 4121.4182126697 3940.4227375566) (10 4128.9592760181 3963.0471719457))
((0 . "LWPOLYLINE") (100 . "AcDbEntity") (8 . "PLANTS") (62 . 94) (370 . 13) (100 . "AcDbPolyline") (90 . 3) (70 . 0)
(43 . 0.0) (10 4121.4182126697 3925.3393665158) (10 4147.8063348416 3920.3643665158) (10 4155.3548642534
3910.2559954751))
((0 . "LWPOLYLINE") (100 . "AcDbEntity") (8 . "PLANTS") (62 . 94) (370 . 13) (100 . "AcDbPolyline") (90 . 2) (70 . 0)
(43 . 0.0) (10 4121.4182126697 369.5333710407) (10 4128.9592760181 369.5333710407))
((0 . "LWPOLYLINE") (100 . "AcDbEntity") (8 . "PLANTS") (62 . 94) (370 . 13) (100 . "AcDbPolyline") (90 . 3) (70 . 0)
(43 . 0.0) (10 4166.667081448 3966.817081448) (10 4159.1185520362 3963.1950226244) (10 4128.9592760181 3963.0471719457))
((0 . "LWPOLYLINE") (100 . "AcDbEntity") (8 . "PLANTS") (62 . 94) (370 . 13) (100 . "AcDbPolyline") (90 . 2) (70 . 0)
(43 . 0.0) (10 4128.9592760181 377.0729638009) (10 4128.9592760181 369.5333710407))
((0 . "LWPOLYLINE") (100 . "AcDbEntity") (8 . "PLANTS") (62 . 94) (370 . 13) (100 . "AcDbPolyline") (90 . 3) (70 . 0)
(43 . 0.0) (10 4147.8125565611 414.782239819) (10 4130.163800905 395.9213800905) (10 4128.9592760181 377.0729638009))
((0 . "LWPOLYLINE") (100 . "AcDbEntity") (8 . "PLANTS") (62 . 94) (370 . 13) (100 . "AcDbPolyline") (90 . 2) (70 . 0)
(43 . 0.0) (10 4166.667081448 388.3851809955) (10 4128.9592760181 377.0729638009))
((0 . "LWPOLYLINE") (100 . "AcDbEntity") (8 . "PLANTS") (62 . 94) (370 . 13) (100 . "AcDbPolyline") (90 . 3) (70 . 0)
(43 . 0.0) (10 4147.8125565611 320.5118778281) (10 4137.7050904977 335.596719457) (10 4128.9592760181 369.5333710407))
((0 . "LWPOLYLINE") (100 . "AcDbEntity") (8 . "PLANTS") (62 . 94) (370 . 13) (100 . "AcDbPolyline") (90 . 2) (70 . 0)
(43 . 0.0) (10 4132.7304298643 6945.7013574661) (10 4136.5003393665 6953.2430995475))
((0 . "LWPOLYLINE") (100 . "AcDbEntity") (8 . "PLANTS") (62 . 94) (370 . 13) (100 . "AcDbPolyline") (90 . 3) (70 . 0)
(43 . 0.0) (10 4155.3548642534 3910.2559954751) (10 4140.4261312217 3901.6713800905) (10 4136.5003393665
3895.1738687783))
((0 . "LWPOLYLINE") (100 . "AcDbEntity") (8 . "PLANTS") (62 . 94) (370 . 13) (100 . "AcDbPolyline") (90 . 2) (70 . 0)
(43 . 0.0) (10 4155.3548642534 1074.6606334842) (10 4152.5614188219 1073.2644135333))
((0 . "LWPOLYLINE") (100 . "AcDbEntity") (8 . "PLANTS") (62 . 94) (370 . 13) (100 . "AcDbPolyline") (90 . 3) (70 . 0)
(43 . 0.0) (10 4144.0426470588 4091.2514705882) (10 4151.5899321267 4084.9014705882) (10 4168.5520361991
4079.9392533937))
((0 . "LWPOLYLINE") (100 . "AcDbEntity") (8 . "PLANTS") (62 . 94) (370 . 13) (100 . "AcDbPolyline") (90 . 3) (70 . 0)
(43 . 0.0) (10 4166.667081448 388.3851809955) (10 4165.4623303167 399.69739819) (10 4147.8125565611 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4196.8325791855 437.4066742081 0.0) (10 4186.1995896042 448.3770089267 0.0) (10 4133.6894420001
444.1001840786 0.0) (10 4147.8125565611 414.782239819 0.0))
((0 . "LWPOLYLINE") (100 . "AcDbEntity") (8 . "PLANTS") (62 . 94) (370 . 13) (100 . "AcDbPolyline") (90 . 2) (70 . 0)
(43 . 0.0) (10 4147.8125565611 320.5118778281) (10 4166.667081448 320.5118778281))
((0 . "LWPOLYLINE") (100 . "AcDbEntity") (8 . "PLANTS") (62 . 94) (370 . 13) (100 . "AcDbPolyline") (90 . 2) (70 . 0)
(43 . 0.0) (10 4147.8125565611 320.5118778281) (10 4147.8125565611 312.9722850679))
((0 . "LWPOLYLINE") (100 . "AcDbEntity") (8 . "PLANTS") (62 . 94) (370 . 13) (100 . "AcDbPolyline") (90 . 3) (70 . 0)
(43 . 0.0) (10 4159.1247737557 6889.1402714932) (10 4152.7813348416 6896.6885746606) (10 4151.5837104072
6907.9942307692))
((0 . "LWPOLYLINE") (100 . "AcDbEntity") (8 . "PLANTS") (62 . 94) (370 . 13) (100 . "AcDbPolyline") (90 . 3) (70 . 0)
(43 . 0.0) (10 4177.9792986425 6919.3064479638) (10 4159.1316742081 6918.1021493213) (10 4151.5837104072
6907.9942307692))
((0 . "LWPOLYLINE") (100 . "AcDbEntity") (8 . "PLANTS") (62 . 94) (370 . 13) (100 . "AcDbPolyline") (90 . 2) (70 . 0)
(43 . 0.0) (10 4172.5929217841 897.4349547511) (10 4185.520361991 897.4349547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4153.4684011958 919.7468954375 0.0) (10 4157.7599466708 931.8270840717 0.0) (10 4173.8655901065
937.1912079578 0.0) (10 4185.520361991 935.1442307692 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4211.9159502262 3857.4660633484 0.0) (10 4189.6780270336 3881.3564764379 0.0) (10 4223.3542769978
3939.4516115924 0.0) (10 4155.3548642534 3910.2559954751 0.0))
((0 . "LWPOLYLINE") (100 . "AcDbEntity") (8 . "PLANTS") (62 . 94) (370 . 13) (100 . "AcDbPolyline") (90 . 2) (70 . 0)
(43 . 0.0) (10 4166.667081448 3966.817081448) (10 4208.1447963801 3966.817081448))
((0 . "LWPOLYLINE") (100 . "AcDbEntity") (8 . "PLANTS") (62 . 94) (370 . 13) (100 . "AcDbPolyline") (90 . 3) (70 . 0)
(43 . 0.0) (10 4170.4369909502 4004.5248868778) (10 4166.8149321267 3996.9769230769) (10 4166.667081448 3966.817081448))
((0 . "LWPOLYLINE") (100 . "AcDbEntity") (8 . "PLANTS") (62 . 94) (370 . 13) (100 . "AcDbPolyline") (90 . 2) (70 . 0)
(43 . 0.0) (10 4166.667081448 388.3851809955) (10 4181.7492081448 343.1363122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4166.667081448 320.5118778281 0.0) (10 4198.1110482805 307.7374383729 0.0) (10 4192.5700511338
271.5270002757 0.0) (10 4215.6858597285 252.6385746606 0.0))
((0 . "LWPOLYLINE") (100 . "AcDbEntity") (8 . "PLANTS") (62 . 94) (370 . 13) (100 . "AcDbPolyline") (90 . 2) (70 . 0)
(43 . 0.0) (10 4166.667081448 320.5118778281) (10 4181.7492081448 343.1363122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4168.5520361991 4079.9392533937 0.0) (10 4198.2129656142 4086.2847737123 0.0) (10 4212.0897529273
4048.6668366642 0.0) (10 4242.0814479638 4061.0859728507 0.0))
((0 . "LWPOLYLINE") (100 . "AcDbEntity") (8 . "PLANTS") (62 . 94) (370 . 13) (100 . "AcDbPolyline") (90 . 3) (70 . 0)
(43 . 0.0) (10 4170.4369909502 4004.5248868778) (10 4166.6733031674 4015.8371040724) (10 4168.5520361991
4079.9392533937))
((0 . "LWPOLYLINE") (100 . "AcDbEntity") (8 . "PLANTS") (62 . 94) (370 . 13) (100 . "AcDbPolyline") (90 . 2) (70 . 0)
(43 . 0.0) (10 4174.2081447964 4113.8759049774) (10 4168.5520361991 4079.9392533937))
((0 . "LWPOLYLINE") (100 . "AcDbEntity") (8 . "PLANTS") (62 . 94) (370 . 13) (100 . "AcDbPolyline") (90 . 3) (70 . 0)
(43 . 0.0) (10 4170.4369909502 4004.5248868778) (10 4193.0552036199 3993.2064479638) (10 4208.1447963801
3966.817081448))
((0 . "LWPOLYLINE") (100 . "AcDbEntity") (8 . "PLANTS") (62 . 94) (370 . 13) (100 . "AcDbPolyline") (90 . 3) (70 . 0)
(43 . 0.0) (10 4176.5496724375 3733.0316742081) (10 4195.6349547511 3766.9683257919) (10 4200.6037330317
3800.9049773756))
((0 . "LWPOLYLINE") (100 . "AcDbEntity") (8 . "PLANTS") (62 . 94) (370 . 13) (100 . "AcDbPolyline") (90 . 2) (70 . 0)
(43 . 0.0) (10 4189.2915158371 248.8687782805) (10 4170.4369909502 267.7234162896))
((0 . "LWPOLYLINE") (100 . "AcDbEntity") (8 . "PLANTS") (62 . 94) (370 . 13) (100 . "AcDbPolyline") (90 . 2) (70 . 0)
(43 . 0.0) (10 4177.9792986425 6919.3064479638) (10 4174.2081447964 6900.4524886878))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4174.2081447964 4193.0614253394 0.0) (10 4178.2361205751 4157.6774625939 0.0) (10 4215.8816345971
4143.4437877653 0.0) (10 4245.85260181 4147.8125565611 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4174.2081447964 4113.8759049774 0.0) (10 4181.3556640846 4138.4820809962 0.0) (10 4155.0403174634
4132.9639337582 0.0) (10 4146.4956284497 4145.9034440097 0.0))
((0 . "LWPOLYLINE") (100 . "AcDbEntity") (8 . "PLANTS") (62 . 94) (370 . 13) (100 . "AcDbPolyline") (90 . 3) (70 . 0)
(43 . 0.0) (10 4140.7239402505 4203.6203260014) (10 4147.8125565611 4198.0367647059) (10 4174.2081447964
4193.0614253394))
((0 . "LWPOLYLINE") (100 . "AcDbEntity") (8 . "PLANTS") (62 . 94) (370 . 13) (100 . "AcDbPolyline") (90 . 2) (70 . 0)
(43 . 0.0) (10 4174.2081447964 4193.0614253394) (10 4174.2094894842 4294.1168402461))
((0 . "LWPOLYLINE") (100 . "AcDbEntity") (8 . "PLANTS") (62 . 94) (370 . 13) (100 . "AcDbPolyline") (90 . 3) (70 . 0)
(43 . 0.0) (10 4174.2081447964 4113.8759049774) (10 4219.4570135747 4092.3081447964) (10 4238.3102941176
4091.2514705882))
((0 . "LWPOLYLINE") (100 . "AcDbEntity") (8 . "PLANTS") (62 . 94) (370 . 13) (100 . "AcDbPolyline") (90 . 3) (70 . 0)
(43 . 0.0) (10 4211.9159502262 7055.0530542986) (10 4203.3182126697 7028.6573529412) (10 4177.9792986425
6998.4919683258))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4177.9792986425 6919.3064479638 0.0) (10 4191.2218369247 6944.934296229 0.0) (10 4230.1814823819
6956.3623714894 0.0) (10 4253.3936651584 6938.1596153846 0.0))
((0 . "LWPOLYLINE") (100 . "AcDbEntity") (8 . "PLANTS") (62 . 94) (370 . 13) (100 . "AcDbPolyline") (90 . 2) (70 . 0)
(43 . 0.0) (10 4181.7492081448 343.1363122172) (10 4234.5403846154 335.596719457))
((0 . "LWPOLYLINE") (100 . "AcDbEntity") (8 . "PLANTS") (62 . 94) (370 . 13) (100 . "AcDbPolyline") (90 . 2) (70 . 0)
(43 . 0.0) (10 4185.520361991 1010.5571266968) (10 4193.0614253394 1010.5571266968))
((0 . "LWPOLYLINE") (100 . "AcDbEntity") (8 . "PLANTS") (62 . 94) (370 . 13) (100 . "AcDbPolyline") (90 . 2) (70 . 0)
(43 . 0.0) (10 4189.3690029851 882.3529411765) (10 4185.520361991 897.4349547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4255.2786199095 912.5197963801 0.0) (10 4234.0732089638 896.015687035 0.0) (10 4206.4857224037
914.2140219878 0.0) (10 4185.520361991 897.4349547511 0.0))
((0 . "LWPOLYLINE") (100 . "AcDbEntity") (8 . "PLANTS") (62 . 94) (370 . 13) (100 . "AcDbPolyline") (90 . 2) (70 . 0)
(43 . 0.0) (10 4189.2915158371 248.8687782805) (10 4215.6858597285 252.6385746606))
((0 . "LWPOLYLINE") (100 . "AcDbEntity") (8 . "PLANTS") (62 . 94) (370 . 13) (100 . "AcDbPolyline") (90 . 3) (70 . 0)
(43 . 0.0) (10 4193.0614253394 1010.5571266968) (10 4204.3805429864 996.5314479638) (10 4219.4570135747 991.7053167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4253.3936651584 1029.4117647059 0.0) (10 4232.9060866802 1037.2391222663 0.0) (10 4202.9034200842
1032.7993893683 0.0) (10 4193.0614253394 1010.5571266968 0.0))
((0 . "LWPOLYLINE") (100 . "AcDbEntity") (8 . "PLANTS") (62 . 94) (370 . 13) (100 . "AcDbPolyline") (90 . 2) (70 . 0)
(43 . 0.0) (10 4196.8325791855 6843.8914027149) (10 4253.3936651584 6843.8914027149))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.3981649483)
(40 . 0.5912826844) (40 . 0.6965916591) (40 . 1) (40 . 1) (40 . 1) (40 . 1) (10 4196.8325791855 6843.8914027149 0.0) (10
4180.3049750954 6876.0889017465 0.0) (10 4212.4642147986 6876.7794838409 0.0) (10 4236.3771956158 6906.9511270223 0.0)
(10 4259.9038199169 6908.9203383453 0.0) (10 4277.5166050598 6884.9215506529 0.0) (10 4291.1014705882 6889.1402714931
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4245.8526018099 3985.6716063348 0.0) (10 4253.4457072065 4019.9794906484 0.0) (10 4209.8670159071
4015.8435065065 0.0) (10 4196.8325791855 4038.4615384615 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4196.8325791855 437.4066742081 0.0) (10 4200.1548153107 421.9226998014 0.0) (10 4211.5168272165
392.673554801 0.0) (10 4234.5403846154 403.4700226244 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4279.7892533937 471.3433257918 0.0) (10 4247.5575962415 485.9590353816 0.0) (10 4212.8102605613
466.4293459179 0.0) (10 4196.8325791855 437.4066742081 0.0))
((0 . "LWPOLYLINE") (100 . "AcDbEntity") (8 . "PLANTS") (62 . 94) (370 . 13) (100 . "AcDbPolyline") (90 . 2) (70 . 0)
(43 . 0.0) (10 4200.6037330317 3800.9049773756) (10 4208.1447963801 3804.6761312217))
((0 . "LWPOLYLINE") (100 . "AcDbEntity") (8 . "PLANTS") (62 . 94) (370 . 13) (100 . "AcDbPolyline") (90 . 2) (70 . 0)
(43 . 0.0) (10 4226.9980769231 3966.817081448) (10 4208.1447963801 3966.817081448))
((0 . "LWPOLYLINE") (100 . "AcDbEntity") (8 . "PLANTS") (62 . 94) (370 . 13) (100 . "AcDbPolyline") (90 . 2) (70 . 0)
(43 . 0.0) (10 4253.3936651584 3804.6761312217) (10 4208.1447963801 3804.6761312217))
((0 . "LWPOLYLINE") (100 . "AcDbEntity") (8 . "PLANTS") (62 . 94) (370 . 13) (100 . "AcDbPolyline") (90 . 2) (70 . 0)
(43 . 0.0) (10 4208.1447963801 3804.6761312217) (10 4211.9159502262 3857.4660633484))
((0 . "LWPOLYLINE") (100 . "AcDbEntity") (8 . "PLANTS") (62 . 94) (370 . 13) (100 . "AcDbPolyline") (90 . 2) (70 . 0)
(43 . 0.0) (10 4211.9159502262 7055.0530542986) (10 4226.9980769231 7066.3652714932))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4211.9159502262 3857.4660633484 0.0) (10 4236.3015144118 3859.9415950827 0.0) (10 4232.8862806752
3891.1620308192 0.0) (10 4253.3936651584 3898.9437782805 0.0))
((0 . "LWPOLYLINE") (100 . "AcDbEntity") (8 . "PLANTS") (62 . 94) (370 . 13) (100 . "AcDbPolyline") (90 . 2) (70 . 0)
(43 . 0.0) (10 4230.1387104072 3733.0316742081) (10 4272.2469457014 3778.2805429864))
((0 . "LWPOLYLINE") (100 . "AcDbEntity") (8 . "PLANTS") (62 . 94) (370 . 13) (100 . "AcDbPolyline") (90 . 3) (70 . 0)
(43 . 0.0) (10 4211.9159502262 938.9140271493) (10 4212.9713800905 953.9911764706) (10 4219.4570135747 961.5384615385))
((0 . "LWPOLYLINE") (100 . "AcDbEntity") (8 . "PLANTS") (62 . 94) (370 . 13) (100 . "AcDbPolyline") (90 . 2) (70 . 0)
(43 . 0.0) (10 4215.6858597285 252.6385746606) (10 4230.7692307692 252.6385746606))
((0 . "LWPOLYLINE") (100 . "AcDbEntity") (8 . "PLANTS") (62 . 94) (370 . 13) (100 . "AcDbPolyline") (90 . 2) (70 . 0)
(43 . 0.0) (10 4219.4570135747 991.7053167421) (10 4219.4570135747 961.5384615385))
((0 . "LWPOLYLINE") (100 . "AcDbEntity") (8 . "PLANTS") (62 . 94) (370 . 13) (100 . "AcDbPolyline") (90 . 3) (70 . 0)
(43 . 0.0) (10 4268.4770361991 991.7053167421) (10 4238.3102941176 995.178959276) (10 4219.4570135747 991.7053167421))
((0 . "LWPOLYLINE") (100 . "AcDbEntity") (8 . "PLANTS") (62 . 94) (370 . 13) (100 . "AcDbPolyline") (90 . 2) (70 . 0)
(43 . 0.0) (10 4226.9980769231 961.5384615385) (10 4219.4570135747 961.5384615385))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6304667025) (40
. 1) (40 . 1) (40 . 1) (40 . 1) (10 4223.2281674208 1112.3670814479 0.0) (10 4252.2465094707 1122.6697050078 0.0) (10
4295.1741613107 1107.9088908271 0.0) (10 4335.1906018395 1087.6195157081 0.0) (10 4351.4324660633 1085.9728506787 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4226.9980769231 3966.817081448 0.0) (10 4225.7388934271 3948.1219897593 0.0) (10 4253.3028210456
3944.3218678874 0.0) (10 4253.3936651584 3925.3393665158 0.0))
((0 . "LWPOLYLINE") (100 . "AcDbEntity") (8 . "PLANTS") (62 . 94) (370 . 13) (100 . "AcDbPolyline") (90 . 3) (70 . 0)
(43 . 0.0) (10 4245.85260181 3985.6716063348) (10 4234.5466063348 3978.1230769231) (10 4226.9980769231 3966.817081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4296.7575791855 243.2126696833 0.0) (10 4278.0924828762 226.413939465 0.0) (10 4243.3379979793
227.7857964127 0.0) (10 4230.7692307692 252.6385746606 0.0))
((0 . "LWPOLYLINE") (100 . "AcDbEntity") (8 . "PLANTS") (62 . 94) (370 . 13) (100 . "AcDbPolyline") (90 . 2) (70 . 0)
(43 . 0.0) (10 4238.3102941176 263.9507918552) (10 4230.7692307692 252.6385746606))
((0 . "LWPOLYLINE") (100 . "AcDbEntity") (8 . "PLANTS") (62 . 94) (370 . 13) (100 . "AcDbPolyline") (90 . 2) (70 . 0)
(43 . 0.0) (10 4234.5403846154 429.8642533937) (10 4234.5403846154 403.4700226244))
((0 . "LWPOLYLINE") (100 . "AcDbEntity") (8 . "PLANTS") (62 . 94) (370 . 13) (100 . "AcDbPolyline") (90 . 3) (70 . 0)
(43 . 0.0) (10 4264.7058823529 388.3851809955) (10 4249.6225113122 389.5900452489) (10 4234.5403846154 403.4700226244))
((0 . "LWPOLYLINE") (100 . "AcDbEntity") (8 . "PLANTS") (62 . 94) (370 . 13) (100 . "AcDbPolyline") (90 . 2) (70 . 0)
(43 . 0.0) (10 4234.5403846154 335.596719457) (10 4245.85260181 316.742081448))
((0 . "LWPOLYLINE") (100 . "AcDbEntity") (8 . "PLANTS") (62 . 94) (370 . 13) (100 . "AcDbPolyline") (90 . 2) (70 . 0)
(43 . 0.0) (10 4234.5403846154 335.596719457) (10 4242.0814479638 365.7607466063))
((0 . "LWPOLYLINE") (100 . "AcDbEntity") (8 . "PLANTS") (62 . 94) (370 . 13) (100 . "AcDbPolyline") (90 . 2) (70 . 0)
(43 . 0.0) (10 4238.3102941176 4091.2514705882) (10 4242.0814479638 4061.0859728507))
((0 . "LWPOLYLINE") (100 . "AcDbEntity") (8 . "PLANTS") (62 . 94) (370 . 13) (100 . "AcDbPolyline") (90 . 3) (70 . 0)
(43 . 0.0) (10 4249.6225113122 4125.1881221719) (10 4239.3669683258 4113.8759049774) (10 4238.3102941176
4091.2514705882))
((0 . "LWPOLYLINE") (100 . "AcDbEntity") (8 . "PLANTS") (62 . 94) (370 . 13) (100 . "AcDbPolyline") (90 . 2) (70 . 0)
(43 . 0.0) (10 5974.7476171011 565.6171700025) (10 6023.1118150174 565.6171534205))
((0 . "LWPOLYLINE") (100 . "AcDbEntity") (8 . "PLANTS") (62 . 94) (370 . 13) (100 . "AcDbPolyline") (90 . 2) (70 . 0)
(43 . 0.0) (10 4238.3102941176 263.9507918552) (10 4245.85260181 316.742081448))
((0 . "LWPOLYLINE") (100 . "AcDbEntity") (8 . "PLANTS") (62 . 94) (370 . 13) (100 . "AcDbPolyline") (90 . 2) (70 . 0)
(43 . 0.0) (10 4238.3102941176 263.9507918552) (10 4268.4770361991 271.4932126697))
((0 . "LWPOLYLINE") (100 . "AcDbEntity") (8 . "PLANTS") (62 . 94) (370 . 13) (100 . "AcDbPolyline") (90 . 3) (70 . 0)
(43 . 0.0) (10 4242.0814479638 4061.0859728507) (10 4272.395361991 4027.29739819) (10 4298.6425339367 4015.8371040724))
((0 . "LWPOLYLINE") (100 . "AcDbEntity") (8 . "PLANTS") (62 . 94) (370 . 13) (100 . "AcDbPolyline") (90 . 2) (70 . 0)
(43 . 0.0) (10 4245.85260181 6870.2863122172) (10 4253.3936651584 6843.8914027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4243.1290867218 4252.7650819036 0.0) (10 4231.282513822 4219.5913525738 0.0) (10 4243.3186914322
4181.7944151877 0.0) (10 4245.85260181 4147.8125565611 0.0))
((0 . "LWPOLYLINE") (100 . "AcDbEntity") (8 . "PLANTS") (62 . 94) (370 . 13) (100 . "AcDbPolyline") (90 . 2) (70 . 0)
(43 . 0.0) (10 4249.6225113122 4125.1881221719) (10 4245.85260181 4147.8125565611))
((0 . "LWPOLYLINE") (100 . "AcDbEntity") (8 . "PLANTS") (62 . 94) (370 . 13) (100 . "AcDbPolyline") (90 . 3) (70 . 0)
(43 . 0.0) (10 4245.85260181 3985.6716063348) (10 4268.4770361991 3971.6449095023) (10 4309.9547511312 3963.0471719457))
((0 . "LWPOLYLINE") (100 . "AcDbEntity") (8 . "PLANTS") (62 . 94) (370 . 13) (100 . "AcDbPolyline") (90 . 2) (70 . 0)
(43 . 0.0) (10 4272.2469457014 316.742081448) (10 4245.85260181 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4249.6225113122 4125.1881221719 0.0) (10 4276.3144539705 4115.8793446497 0.0) (10 4266.5582880693
4073.2453479516 0.0) (10 4298.6425339367 4072.3981900452 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5908373183)
(40 . 0.8814534637) (40 . 1) (40 . 1) (40 . 1) (40 . 1) (10 4349.5475113122 1012.443438914 0.0) (10 4333.9423787483
1034.8225702085 0.0) (10 4281.2001659569 1022.8808782808 0.0) (10 4277.1953969589 1082.0911506505 0.0) (10
4255.8311870132 1078.2486549345 0.0) (10 4249.6225113122 1074.6606334841 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4419.3057692308 6836.3496606335 0.0) (10 4365.0849884061 6855.176939129 0.0) (10 4308.4668311921
6831.4731578846 0.0) (10 4253.3936651584 6843.8914027149 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3708582466) (40
. 1) (40 . 1) (40 . 1) (40 . 1) (10 4347.6625565612 3883.8616515839 0.0) (10 4339.3186542934 3892.1308668016 0.0) (10
4304.4469521656 3901.6067877851 0.0) (10 4276.7866801269 3926.2869749927 0.0) (10 4253.3936651584 3925.3393665159 0.0))
((0 . "LWPOLYLINE") (100 . "AcDbEntity") (8 . "PLANTS") (62 . 94) (370 . 13) (100 . "AcDbPolyline") (90 . 2) (70 . 0)
(43 . 0.0) (10 4253.3936651584 3925.3393665158) (10 4253.3936651584 3898.9437782805))
((0 . "LWPOLYLINE") (100 . "AcDbEntity") (8 . "PLANTS") (62 . 94) (370 . 13) (100 . "AcDbPolyline") (90 . 3) (70 . 0)
(43 . 0.0) (10 4253.3936651584 3898.9437782805) (10 4289.896719457 3865.0071266968) (10 4294.8713800905
3831.0704751131))
((0 . "LWPOLYLINE") (100 . "AcDbEntity") (8 . "PLANTS") (62 . 94) (370 . 13) (100 . "AcDbPolyline") (90 . 2) (70 . 0)
(43 . 0.0) (10 4253.3936651584 3804.6761312217) (10 4272.2469457014 3778.2805429864))
((0 . "LWPOLYLINE") (100 . "AcDbEntity") (8 . "PLANTS") (62 . 94) (370 . 13) (100 . "AcDbPolyline") (90 . 2) (70 . 0)
(43 . 0.0) (10 4279.7892533937 3827.3005656109) (10 4253.3936651584 3804.6761312217))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4255.2786199095 912.5197963801 0.0) (10 4284.9763749305 885.4420604897 0.0) (10 4341.3336922657
888.9433448489 0.0) (10 4366.5158371041 920.0593891403 0.0))
((0 . "LWPOLYLINE") (100 . "AcDbEntity") (8 . "PLANTS") (62 . 94) (370 . 13) (100 . "AcDbPolyline") (90 . 3) (70 . 0)
(43 . 0.0) (10 4260.9347285068 920.0593891403) (10 4253.3936651584 916.2895927602) (10 4255.2786199095 912.5197963801))
((0 . "LWPOLYLINE") (100 . "AcDbEntity") (8 . "PLANTS") (62 . 94) (370 . 13) (100 . "AcDbPolyline") (90 . 2) (70 . 0)
(43 . 0.0) (10 4260.9347285068 920.0593891403) (10 4255.2786199095 912.5197963801))
((0 . "LWPOLYLINE") (100 . "AcDbEntity") (8 . "PLANTS") (62 . 94) (370 . 13) (100 . "AcDbPolyline") (90 . 2) (70 . 0)
(43 . 0.0) (10 4279.7892533937 3827.3005656109) (10 4257.1648190045 3857.4660633484))
((0 . "LWPOLYLINE") (100 . "AcDbEntity") (8 . "PLANTS") (62 . 94) (370 . 13) (100 . "AcDbPolyline") (90 . 2) (70 . 0)
(43 . 0.0) (10 4260.9347285068 920.0593891403) (10 4260.9347285068 935.1442307692))
((0 . "LWPOLYLINE") (100 . "AcDbEntity") (8 . "PLANTS") (62 . 94) (370 . 13) (100 . "AcDbPolyline") (90 . 3) (70 . 0)
(43 . 0.0) (10 4268.4770361991 961.5384615385) (10 4262.1325791855 953.9911764706) (10 4260.9347285068 935.1442307692))
((0 . "LWPOLYLINE") (100 . "AcDbEntity") (8 . "PLANTS") (62 . 94) (370 . 13) (100 . "AcDbPolyline") (90 . 3) (70 . 0)
(43 . 0.0) (10 4300.5274886878 959.6521493213) (10 4287.3240950226 936.3476244344) (10 4260.9347285068 935.1442307692))
((0 . "LWPOLYLINE") (100 . "AcDbEntity") (8 . "PLANTS") (62 . 94) (370 . 13) (100 . "AcDbPolyline") (90 . 2) (70 . 0)
(43 . 0.0) (10 4268.4770361991 991.7053167421) (10 4268.4770361991 961.5384615385))
((0 . "LWPOLYLINE") (100 . "AcDbEntity") (8 . "PLANTS") (62 . 94) (370 . 13) (100 . "AcDbPolyline") (90 . 3) (70 . 0)
(43 . 0.0) (10 4268.4770361991 991.7053167421) (10 4287.3303167421 995.3266968326) (10 4302.4136877828 987.9326923077))
((0 . "LWPOLYLINE") (100 . "AcDbEntity") (8 . "PLANTS") (62 . 94) (370 . 13) (100 . "AcDbPolyline") (90 . 2) (70 . 0)
(43 . 0.0) (10 4268.4770361991 961.5384615385) (10 4300.5274886878 959.6521493213))
((0 . "LWPOLYLINE") (100 . "AcDbEntity") (8 . "PLANTS") (62 . 94) (370 . 13) (100 . "AcDbPolyline") (90 . 2) (70 . 0)
(43 . 0.0) (10 4296.7575791855 243.2126696833) (10 4268.4770361991 271.4932126697))
((0 . "LWPOLYLINE") (100 . "AcDbEntity") (8 . "PLANTS") (62 . 94) (370 . 13) (100 . "AcDbPolyline") (90 . 3) (70 . 0)
(43 . 0.0) (10 4272.2469457014 316.742081448) (10 4272.0990950226 279.0404977376) (10 4268.4770361991 271.4932126697))
((0 . "LWPOLYLINE") (100 . "AcDbEntity") (8 . "PLANTS") (62 . 94) (370 . 13) (100 . "AcDbPolyline") (90 . 2) (70 . 0)
(43 . 0.0) (10 4340.1202488688 3774.5093891403) (10 4272.2469457014 3778.2805429864))
((0 . "LWPOLYLINE") (100 . "AcDbEntity") (8 . "PLANTS") (62 . 94) (370 . 13) (100 . "AcDbPolyline") (90 . 3) (70 . 0)
(43 . 0.0) (10 4272.2469457014 316.742081448) (10 4287.175678733 324.4377828054) (10 4302.4136877828 354.4485294118))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4299.5389982947 6730.7692307692 0.0) (10 4320.318960634 6737.4947268712 0.0) (10 4336.0115780177
6760.2892701672 0.0) (10 4328.8080316742 6783.559841629 0.0))
((0 . "LWPOLYLINE") (100 . "AcDbEntity") (8 . "PLANTS") (62 . 94) (370 . 13) (100 . "AcDbPolyline") (90 . 3) (70 . 0)
(43 . 0.0) (10 4279.7892533937 3827.3005656109) (10 4291.1014705882 3827.3005656109) (10 4294.8713800905
3831.0704751131))
((0 . "LWPOLYLINE") (100 . "AcDbEntity") (8 . "PLANTS") (62 . 94) (370 . 13) (100 . "AcDbPolyline") (90 . 2) (70 . 0)
(43 . 0.0) (10 4279.7892533937 1150.0763574661) (10 4313.7259049774 1127.4519230769))
((0 . "LWPOLYLINE") (100 . "AcDbEntity") (8 . "PLANTS") (62 . 94) (370 . 13) (100 . "AcDbPolyline") (90 . 3) (70 . 0)
(43 . 0.0) (10 4302.4136877828 354.4485294118) (10 4297.4449095023 377.0680995475) (10 4291.1014705882 384.6153846154))
((0 . "LWPOLYLINE") (100 . "AcDbEntity") (8 . "PLANTS") (62 . 94) (370 . 13) (100 . "AcDbPolyline") (90 . 2) (70 . 0)
(43 . 0.0) (10 4332.5791855204 3831.0704751131) (10 4294.8713800905 3831.0704751131))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4296.7575791855 243.2126696833 0.0) (10 4327.2209099505 234.2211577281 0.0) (10 4372.377010126
214.8985140758 0.0) (10 4392.9114253394 252.6385746606 0.0))
((0 . "LWPOLYLINE") (100 . "AcDbEntity") (8 . "PLANTS") (62 . 94) (370 . 13) (100 . "AcDbPolyline") (90 . 3) (70 . 0)
(43 . 0.0) (10 4296.7575791855 243.2126696833) (10 4312.6754524887 271.4932126697) (10 4313.7259049774 301.6600678733))
((0 . "LWPOLYLINE") (100 . "AcDbEntity") (8 . "PLANTS") (62 . 94) (370 . 13) (100 . "AcDbPolyline") (90 . 2) (70 . 0)
(43 . 0.0) (10 4298.6425339367 4072.3981900452) (10 4298.6425339367 4015.8371040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4323.7782954444 4204.37555667 0.0) (10 4332.8610902196 4159.9742457385 0.0) (10 4311.2481294895
4113.8414363284 0.0) (10 4298.6425339367 4072.3981900452 0.0))
((0 . "LWPOLYLINE") (100 . "AcDbEntity") (8 . "PLANTS") (62 . 94) (370 . 13) (100 . "AcDbPolyline") (90 . 2) (70 . 0)
(43 . 0.0) (10 4309.9547511312 3963.0471719457) (10 4298.6425339367 4015.8371040724))
((0 . "LWPOLYLINE") (100 . "AcDbEntity") (8 . "PLANTS") (62 . 94) (370 . 13) (100 . "AcDbPolyline") (90 . 2) (70 . 0)
(43 . 0.0) (10 4298.6425339367 3657.6173076923) (10 4317.4958144796 3657.6173076923))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4298.6425339367 3619.9095022624 0.0) (10 4282.5480717474 3623.0568975325 0.0) (10 4277.8662628078
3658.8472680791 0.0) (10 4298.6425339367 3657.6173076923 0.0))
((0 . "LWPOLYLINE") (100 . "AcDbEntity") (8 . "PLANTS") (62 . 94) (370 . 13) (100 . "AcDbPolyline") (90 . 2) (70 . 0)
(43 . 0.0) (10 4298.6425339367 3657.6173076923) (10 4302.4136877828 3691.553959276))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3788382128)
(40 . 0.5702480369) (40 . 1) (40 . 1) (40 . 1) (40 . 1) (10 4340.1202488688 3601.0555429864 0.0) (10 4327.5188151795
3604.5293123045 0.0) (10 4311.4978162632 3583.6889454326 0.0) (10 4279.3227232012 3576.2158904309 0.0) (10
4279.3594826216 3611.652450746 0.0) (10 4298.6425339367 3619.9095022625 0.0))
((0 . "LWPOLYLINE") (100 . "AcDbEntity") (8 . "PLANTS") (62 . 94) (370 . 13) (100 . "AcDbPolyline") (90 . 2) (70 . 0)
(43 . 0.0) (10 4321.2669683258 3634.9928733032) (10 4298.6425339367 3619.9095022624))
((0 . "LWPOLYLINE") (100 . "AcDbEntity") (8 . "PLANTS") (62 . 94) (370 . 13) (100 . "AcDbPolyline") (90 . 2) (70 . 0)
(43 . 0.0) (10 4302.4136877828 987.9326923077) (10 4300.5274886878 959.6521493213))
((0 . "LWPOLYLINE") (100 . "AcDbEntity") (8 . "PLANTS") (62 . 94) (370 . 13) (100 . "AcDbPolyline") (90 . 3) (70 . 0)
(43 . 0.0) (10 4300.5274886878 959.6521493213) (10 4336.2019230769 973.0053167421) (10 4347.6625565611 995.4751131222))
((0 . "LWPOLYLINE") (100 . "AcDbEntity") (8 . "PLANTS") (62 . 94) (370 . 13) (100 . "AcDbPolyline") (90 . 2) (70 . 0)
(43 . 0.0) (10 4332.5791855204 3729.260520362) (10 4302.4136877828 3721.7194570136))
((0 . "LWPOLYLINE") (100 . "AcDbEntity") (8 . "PLANTS") (62 . 94) (370 . 13) (100 . "AcDbPolyline") (90 . 3) (70 . 0)
(43 . 0.0) (10 4302.4136877828 987.9326923077) (10 4328.8080316742 995.3273755656) (10 4347.6625565611 995.4751131222))
((0 . "LWPOLYLINE") (100 . "AcDbEntity") (8 . "PLANTS") (62 . 94) (370 . 13) (100 . "AcDbPolyline") (90 . 2) (70 . 0)
(43 . 0.0) (10 4351.4324660633 350.6787330317) (10 4302.4136877828 354.4485294118))
((0 . "LWPOLYLINE") (100 . "AcDbEntity") (8 . "PLANTS") (62 . 94) (370 . 13) (100 . "AcDbPolyline") (90 . 3) (70 . 0)
(43 . 0.0) (10 4343.8914027149 3951.7349547511) (10 4328.8080316742 3952.7910633484) (10 4309.9547511312
3963.0471719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4351.4324660633 365.7607466063 0.0) (10 4326.162794996 384.0669429276 0.0) (10 4338.6457695032
423.0760302401 0.0) (10 4313.7259049774 441.1764705882 0.0))
((0 . "LWPOLYLINE") (100 . "AcDbEntity") (8 . "PLANTS") (62 . 94) (370 . 13) (100 . "AcDbPolyline") (90 . 2) (70 . 0)
(43 . 0.0) (10 4321.2669683258 3634.9928733032) (10 4317.4958144796 3657.6173076923))
((0 . "LWPOLYLINE") (100 . "AcDbEntity") (8 . "PLANTS") (62 . 94) (370 . 13) (100 . "AcDbPolyline") (90 . 2) (70 . 0)
(43 . 0.0) (10 4343.8914027149 3672.6994343891) (10 4317.4958144796 3657.6173076923))
((0 . "LWPOLYLINE") (100 . "AcDbEntity") (8 . "PLANTS") (62 . 94) (370 . 13) (100 . "AcDbPolyline") (90 . 2) (70 . 0)
(43 . 0.0) (10 4321.2669683258 3634.9928733032) (10 4351.4324660633 3634.9928733032))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4370.2869909502 6817.4964932127 0.0) (10 4371.8371749551 6795.7985857299 0.0) (10 4349.5014087066
6778.2114003705 0.0) (10 4328.8080316742 6783.559841629 0.0))
((0 . "LWPOLYLINE") (100 . "AcDbEntity") (8 . "PLANTS") (62 . 94) (370 . 13) (100 . "AcDbPolyline") (90 . 2) (70 . 0)
(43 . 0.0) (10 4358.5599388612 3242.0401672743) (10 4366.5158371041 3242.8358597285))
((0 . "LWPOLYLINE") (100 . "AcDbEntity") (8 . "PLANTS") (62 . 94) (370 . 13) (100 . "AcDbPolyline") (90 . 3) (70 . 0)
(43 . 0.0) (10 4389.1402714932 3831.0704751131) (10 4370.2869909502 3827.3005656109) (10 4332.5791855204
3831.0704751131))
((0 . "LWPOLYLINE") (100 . "AcDbEntity") (8 . "PLANTS") (62 . 94) (370 . 13) (100 . "AcDbPolyline") (90 . 3) (70 . 0)
(43 . 0.0) (10 4347.6625565611 3883.8616515837) (10 4337.3998868778 3865.0071266968) (10 4332.5791855204
3831.0704751131))
((0 . "LWPOLYLINE") (100 . "AcDbEntity") (8 . "PLANTS") (62 . 94) (370 . 13) (100 . "AcDbPolyline") (90 . 2) (70 . 0)
(43 . 0.0) (10 4332.5791855204 3729.260520362) (10 4343.8914027149 3714.1783936652))
((0 . "LWPOLYLINE") (100 . "AcDbEntity") (8 . "PLANTS") (62 . 94) (370 . 13) (100 . "AcDbPolyline") (90 . 3) (70 . 0)
(43 . 0.0) (10 4332.5791855204 3729.260520362) (10 4336.5042986425 3739.5173076923) (10 4355.2036199095
3744.3438914027))
((0 . "LWPOLYLINE") (100 . "AcDbEntity") (8 . "PLANTS") (62 . 94) (370 . 13) (100 . "AcDbPolyline") (90 . 3) (70 . 0)
(43 . 0.0) (10 4368.4007918552 3925.3393665158) (10 4347.8165158371 3940.5702488688) (10 4343.8914027149
3951.7349547511))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3918260725)
(40 . 0.8692935394) (40 . 1) (40 . 1) (40 . 1) (40 . 1) (10 4343.8914027149 3951.7349547511 0.0) (10 4364.6869859241
3968.0397209345 0.0) (10 4348.717357388 4022.6410253341 0.0) (10 4362.8188308448 4078.5988344061 0.0) (10
4361.4943683945 4113.818027991 0.0) (10 4362.7446832578 4121.4182126697 0.0))
((0 . "LWPOLYLINE") (100 . "AcDbEntity") (8 . "PLANTS") (62 . 94) (370 . 13) (100 . "AcDbPolyline") (90 . 2) (70 . 0)
(43 . 0.0) (10 4355.2036199095 3714.1783936652) (10 4343.8914027149 3714.1783936652))
((0 . "LWPOLYLINE") (100 . "AcDbEntity") (8 . "PLANTS") (62 . 94) (370 . 13) (100 . "AcDbPolyline") (90 . 2) (70 . 0)
(43 . 0.0) (10 4343.8914027149 3714.1783936652) (10 4343.8914027149 3672.6994343891))
((0 . "LWPOLYLINE") (100 . "AcDbEntity") (8 . "PLANTS") (62 . 94) (370 . 13) (100 . "AcDbPolyline") (90 . 2) (70 . 0)
(43 . 0.0) (10 4343.8914027149 3672.6994343891) (10 4358.9747737557 3672.6994343891))
((0 . "LWPOLYLINE") (100 . "AcDbEntity") (8 . "PLANTS") (62 . 94) (370 . 13) (100 . "AcDbPolyline") (90 . 2) (70 . 0)
(43 . 0.0) (10 4347.6625565611 3883.8616515837) (10 4355.2036199095 3883.8616515837))
((0 . "LWPOLYLINE") (100 . "AcDbEntity") (8 . "PLANTS") (62 . 94) (370 . 13) (100 . "AcDbPolyline") (90 . 2) (70 . 0)
(43 . 0.0) (10 4349.5475113122 1012.443438914) (10 4347.6625565611 995.4751131222))
((0 . "LWPOLYLINE") (100 . "AcDbEntity") (8 . "PLANTS") (62 . 94) (370 . 13) (100 . "AcDbPolyline") (90 . 3) (70 . 0)
(43 . 0.0) (10 4347.6625565611 946.4564479638) (10 4352.4891402715 935.1442307692) (10 4366.5158371041 920.0593891403))
((0 . "LWPOLYLINE") (100 . "AcDbEntity") (8 . "PLANTS") (62 . 94) (370 . 13) (100 . "AcDbPolyline") (90 . 3) (70 . 0)
(43 . 0.0) (10 4385.3691176471 263.9507918552) (10 4358.9747737557 264.1061085973) (10 4347.6625565611 271.4932126697))
((0 . "LWPOLYLINE") (100 . "AcDbEntity") (8 . "PLANTS") (62 . 94) (370 . 13) (100 . "AcDbPolyline") (90 . 2) (70 . 0)
(43 . 0.0) (10 4349.5475113122 1012.443438914) (10 4351.4324660633 1085.9728506787))
((0 . "LWPOLYLINE") (100 . "AcDbEntity") (8 . "PLANTS") (62 . 94) (370 . 13) (100 . "AcDbPolyline") (90 . 2) (70 . 0)
(43 . 0.0) (10 4349.5475113122 1012.443438914) (10 4411.7647058824 1014.3297511312))
((0 . "LWPOLYLINE") (100 . "AcDbEntity") (8 . "PLANTS") (62 . 94) (370 . 13) (100 . "AcDbPolyline") (90 . 2) (70 . 0)
(43 . 0.0) (10 4351.4324660633 3774.5093891403) (10 4358.9747737557 3766.9683257919))
((0 . "LWPOLYLINE") (100 . "AcDbEntity") (8 . "PLANTS") (62 . 94) (370 . 13) (100 . "AcDbPolyline") (90 . 3) (70 . 0)
(43 . 0.0) (10 4404.2236425339 1134.9915158371) (10 4370.2869909502 1152.7898190045) (10 4351.4324660633
1153.8461538462))
((0 . "LWPOLYLINE") (100 . "AcDbEntity") (8 . "PLANTS") (62 . 94) (370 . 13) (100 . "AcDbPolyline") (90 . 2) (70 . 0)
(43 . 0.0) (10 4351.4324660633 1085.9728506787) (10 4351.4324660633 1153.8461538462))
((0 . "LWPOLYLINE") (100 . "AcDbEntity") (8 . "PLANTS") (62 . 94) (370 . 13) (100 . "AcDbPolyline") (90 . 2) (70 . 0)
(43 . 0.0) (10 6546.003280543 1157.6159502262) (10 6547.8319942172 1166.7757305978))
((0 . "LWPOLYLINE") (100 . "AcDbEntity") (8 . "PLANTS") (62 . 94) (370 . 13) (100 . "AcDbPolyline") (90 . 2) (70 . 0)
(43 . 0.0) (10 4351.7615736647 1245.328027049) (10 4351.4324660633 1153.8461538462))
((0 . "LWPOLYLINE") (100 . "AcDbEntity") (8 . "PLANTS") (62 . 94) (370 . 13) (100 . "AcDbPolyline") (90 . 3) (70 . 0)
(43 . 0.0) (10 4351.4324660633 1085.9728506787) (10 4385.3691176471 1084.9165158371) (10 4407.9935520362
1070.8908371041))
((0 . "LWPOLYLINE") (100 . "AcDbEntity") (8 . "PLANTS") (62 . 94) (370 . 13) (100 . "AcDbPolyline") (90 . 2) (70 . 0)
(43 . 0.0) (10 4351.4324660633 365.7607466063) (10 4351.4324660633 350.6787330317))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4351.4324660633 365.7607466063 0.0) (10 4373.4491574636 383.6832972708 0.0) (10 4353.1723657248
425.5902544787 0.0) (10 4381.5992081448 437.4066742081 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4351.4324660634 350.6787330317 0.0) (10 4375.5185254429 341.2834132729 0.0) (10 4363.2117567036
306.7085921663 0.0) (10 4385.3691176471 294.1176470588 0.0))
((0 . "LWPOLYLINE") (100 . "AcDbEntity") (8 . "PLANTS") (62 . 94) (370 . 13) (100 . "AcDbPolyline") (90 . 3) (70 . 0)
(43 . 0.0) (10 4389.1402714932 3831.0704751131) (10 4380.4010180995 3861.2365384615) (10 4355.2036199095
3883.8616515837))
((0 . "LWPOLYLINE") (100 . "AcDbEntity") (8 . "PLANTS") (62 . 94) (370 . 13) (100 . "AcDbPolyline") (90 . 3) (70 . 0)
(43 . 0.0) (10 4368.4007918552 3925.3393665158) (10 4360.0339366516 3914.0271493213) (10 4355.2036199095
3883.8616515837))
((0 . "LWPOLYLINE") (100 . "AcDbEntity") (8 . "PLANTS") (62 . 94) (370 . 13) (100 . "AcDbPolyline") (90 . 3) (70 . 0)
(43 . 0.0) (10 4355.2036199095 3714.1783936652) (10 4362.4421945701 3736.7959276018) (10 4355.2036199095
3744.3438914027))
((0 . "LWPOLYLINE") (100 . "AcDbEntity") (8 . "PLANTS") (62 . 94) (370 . 13) (100 . "AcDbPolyline") (90 . 2) (70 . 0)
(43 . 0.0) (10 4358.9747737557 3766.9683257919) (10 4355.2036199095 3744.3438914027))
((0 . "LWPOLYLINE") (100 . "AcDbEntity") (8 . "PLANTS") (62 . 94) (370 . 13) (100 . "AcDbPolyline") (90 . 2) (70 . 0)
(43 . 0.0) (10 4355.2036199095 3714.1783936652) (10 4374.0569004525 3691.553959276))
((0 . "LWPOLYLINE") (100 . "AcDbEntity") (8 . "PLANTS") (62 . 94) (370 . 13) (100 . "AcDbPolyline") (90 . 3) (70 . 0)
(43 . 0.0) (10 4355.2036199095 3657.6173076923) (10 4358.9747737557 3661.3872171946) (10 4358.9747737557
3672.6994343891))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4358.9747737557 3766.9683257919 0.0) (10 4374.1448735119 3795.0675381644 0.0) (10 4412.5977952131
3773.8691113099 0.0) (10 4423.0769230769 3808.446040724 0.0))
((0 . "LWPOLYLINE") (100 . "AcDbEntity") (8 . "PLANTS") (62 . 94) (370 . 13) (100 . "AcDbPolyline") (90 . 2) (70 . 0)
(43 . 0.0) (10 4374.0569004525 3691.553959276) (10 4358.9747737557 3672.6994343891))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4366.5158371041 3435.1435520362 0.0) (10 4361.4320797295 3444.7630018181 0.0) (10 4358.9250155399
3468.6514793371 0.0) (10 4374.0569004525 3472.850678733 0.0))
((0 . "LWPOLYLINE") (100 . "AcDbEntity") (8 . "PLANTS") (62 . 94) (370 . 13) (100 . "AcDbPolyline") (90 . 3) (70 . 0)
(43 . 0.0) (10 4366.5158371041 3408.7478506787) (10 4400.3044117647 3424.8869909502) (10 4407.9935520362
3435.1435520362))
((0 . "LWPOLYLINE") (100 . "AcDbEntity") (8 . "PLANTS") (62 . 94) (370 . 13) (100 . "AcDbPolyline") (90 . 2) (70 . 0)
(43 . 0.0) (10 4366.5158371041 3242.8358597285) (10 4400.4524886878 3239.0645927602))
((0 . "LWPOLYLINE") (100 . "AcDbEntity") (8 . "PLANTS") (62 . 94) (370 . 13) (100 . "AcDbPolyline") (90 . 2) (70 . 0)
(43 . 0.0) (10 4366.5158371041 3242.8358597285) (10 4366.5158371041 3235.2941176471))
((0 . "LWPOLYLINE") (100 . "AcDbEntity") (8 . "PLANTS") (62 . 94) (370 . 13) (100 . "AcDbPolyline") (90 . 2) (70 . 0)
(43 . 0.0) (10 4381.5992081448 920.0593891403) (10 4366.5158371041 920.0593891403))
((0 . "LWPOLYLINE") (100 . "AcDbEntity") (8 . "PLANTS") (62 . 94) (370 . 13) (100 . "AcDbPolyline") (90 . 2) (70 . 0)
(43 . 0.0) (10 4368.4007918552 3925.3393665158) (10 4392.9114253394 3917.7983031674))
((0 . "LWPOLYLINE") (100 . "AcDbEntity") (8 . "PLANTS") (62 . 94) (370 . 13) (100 . "AcDbPolyline") (90 . 3) (70 . 0)
(43 . 0.0) (10 4368.4007918552 3925.3393665158) (10 4384.1652714932 3944.1926470588) (10 4385.3691176471
3970.5882352941))
((0 . "LWPOLYLINE") (100 . "AcDbEntity") (8 . "PLANTS") (62 . 94) (370 . 13) (100 . "AcDbPolyline") (90 . 2) (70 . 0)
(43 . 0.0) (10 4370.2869909502 509.0497737557) (10 4374.0569004525 520.3619909502))
((0 . "LWPOLYLINE") (100 . "AcDbEntity") (8 . "PLANTS") (62 . 94) (370 . 13) (100 . "AcDbPolyline") (90 . 2) (70 . 0)
(43 . 0.0) (10 4400.4524886878 3697.2100678733) (10 4374.0569004525 3691.553959276))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4381.5992081448 920.0593891403 0.0) (10 4397.4774965462 887.5987321162 0.0) (10 4447.9077999508
900.5453522038 0.0) (10 4468.3257918552 920.0593891403 0.0))
((0 . "LWPOLYLINE") (100 . "AcDbEntity") (8 . "PLANTS") (62 . 94) (370 . 13) (100 . "AcDbPolyline") (90 . 2) (70 . 0)
(43 . 0.0) (10 4381.5992081448 920.0593891403) (10 4392.9114253394 938.9140271493))
((0 . "LWPOLYLINE") (100 . "AcDbEntity") (8 . "PLANTS") (62 . 94) (370 . 13) (100 . "AcDbPolyline") (90 . 2) (70 . 0)
(43 . 0.0) (10 4400.4524886878 429.8642533937) (10 4381.5992081448 437.4066742081))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4400.4524886878 478.882918552 0.0) (10 4402.2764915417 461.1806456087 0.0) (10 4373.3838299522
457.4235913521 0.0) (10 4381.5992081448 437.4066742081 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7160959767) (40
. 1) (40 . 1) (40 . 1) (40 . 1) (10 4415.5358597284 4144.0426470588 0.0) (10 4405.27368927 4103.663466937 0.0) (10
4400.5912346982 4043.6918703461 0.0) (10 4382.7246317825 3987.7790203052 0.0) (10 4385.369117647 3970.5882352941 0.0))
((0 . "LWPOLYLINE") (100 . "AcDbEntity") (8 . "PLANTS") (62 . 94) (370 . 13) (100 . "AcDbPolyline") (90 . 3) (70 . 0)
(43 . 0.0) (10 4430.6179864253 3989.4415158371) (10 4400.4524886878 3971.6449095023) (10 4385.3691176471
3970.5882352941))
((0 . "LWPOLYLINE") (100 . "AcDbEntity") (8 . "PLANTS") (62 . 94) (370 . 13) (100 . "AcDbPolyline") (90 . 2) (70 . 0)
(43 . 0.0) (10 4385.3691176471 263.9507918552) (10 4385.3691176471 294.1176470588))
((0 . "LWPOLYLINE") (100 . "AcDbEntity") (8 . "PLANTS") (62 . 94) (370 . 13) (100 . "AcDbPolyline") (90 . 3) (70 . 0)
(43 . 0.0) (10 4407.9935520362 324.2845022624) (10 4404.0686651584 312.9722850679) (10 4385.3691176471 294.1176470588))
((0 . "LWPOLYLINE") (100 . "AcDbEntity") (8 . "PLANTS") (62 . 94) (370 . 13) (100 . "AcDbPolyline") (90 . 2) (70 . 0)
(43 . 0.0) (10 4385.3691176471 263.9507918552) (10 4392.9114253394 252.6385746606))
((0 . "LWPOLYLINE") (100 . "AcDbEntity") (8 . "PLANTS") (62 . 94) (370 . 13) (100 . "AcDbPolyline") (90 . 3) (70 . 0)
(43 . 0.0) (10 4389.1402714932 3831.0704751131) (10 4415.528959276 3826.1027149321) (10 4423.0769230769
3819.7582579186))
((0 . "LWPOLYLINE") (100 . "AcDbEntity") (8 . "PLANTS") (62 . 94) (370 . 13) (100 . "AcDbPolyline") (90 . 2) (70 . 0)
(43 . 0.0) (10 4404.2236425339 3367.2702488688) (10 4389.1402714932 3344.6458144796))
((0 . "LWPOLYLINE") (100 . "AcDbEntity") (8 . "PLANTS") (62 . 94) (370 . 13) (100 . "AcDbPolyline") (90 . 3) (70 . 0)
(43 . 0.0) (10 4392.9114253394 3917.7983031674) (10 4426.8480769231 3890.5075791855) (10 4453.2424208145
3887.631561086))
((0 . "LWPOLYLINE") (100 . "AcDbEntity") (8 . "PLANTS") (62 . 94) (370 . 13) (100 . "AcDbPolyline") (90 . 3) (70 . 0)
(43 . 0.0) (10 4392.9114253394 3917.7983031674) (10 4407.9935520362 3931.6765837104) (10 4441.9302036199
3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4392.9114253394 938.9140271493 0.0) (10 4378.0615479987 962.3104280097 0.0) (10 4411.1791515002
986.2366310551 0.0) (10 4426.8480769231 965.3082579185 0.0))
((0 . "LWPOLYLINE") (100 . "AcDbEntity") (8 . "PLANTS") (62 . 94) (370 . 13) (100 . "AcDbPolyline") (90 . 2) (70 . 0)
(43 . 0.0) (10 4392.9114253394 938.9140271493) (10 4404.2236425339 942.6838235294))
((0 . "LWPOLYLINE") (100 . "AcDbEntity") (8 . "PLANTS") (62 . 94) (370 . 13) (100 . "AcDbPolyline") (90 . 2) (70 . 0)
(43 . 0.0) (10 4400.4524886878 478.882918552) (10 4392.9114253394 482.6555429864))
((0 . "LWPOLYLINE") (100 . "AcDbEntity") (8 . "PLANTS") (62 . 94) (370 . 13) (100 . "AcDbPolyline") (90 . 2) (70 . 0)
(43 . 0.0) (10 4407.9935520362 252.6385746606) (10 4392.9114253394 252.6385746606))
((0 . "LWPOLYLINE") (100 . "AcDbEntity") (8 . "PLANTS") (62 . 94) (370 . 13) (100 . "AcDbPolyline") (90 . 3) (70 . 0)
(43 . 0.0) (10 4415.5358597285 4245.85260181) (10 4411.6100678733 4257.009841629) (10 4405.7659775982 4259.0656095381))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4400.4524886878 3697.2100678733 0.0) (10 4414.3691183575 3668.8655602655 0.0) (10 4386.6042845869
3634.387504263 0.0) (10 4407.9935520362 3608.5972850679 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4705883234) (40
. 1) (40 . 1) (40 . 1) (40 . 1) (10 4400.4524886878 3697.2100678733 0.0) (10 4396.2544319011 3719.0007922895 0.0) (10
4412.2993216488 3754.7411043172 0.0) (10 4457.5455412466 3761.061236258 0.0) (10 4460.7847285068 3785.8216063348 0.0))
((0 . "LWPOLYLINE") (100 . "AcDbEntity") (8 . "PLANTS") (62 . 94) (370 . 13) (100 . "AcDbPolyline") (90 . 2) (70 . 0)
(43 . 0.0) (10 4426.8480769231 3706.6360859729) (10 4400.4524886878 3697.2100678733))
((0 . "LWPOLYLINE") (100 . "AcDbEntity") (8 . "PLANTS") (62 . 94) (370 . 13) (100 . "AcDbPolyline") (90 . 2) (70 . 0)
(43 . 0.0) (10 4436.2740950226 3239.0645927602) (10 4400.4524886878 3239.0645927602))
((0 . "LWPOLYLINE") (100 . "AcDbEntity") (8 . "PLANTS") (62 . 94) (370 . 13) (100 . "AcDbPolyline") (90 . 2) (70 . 0)
(43 . 0.0) (10 4400.4524886878 3235.2941176471) (10 4400.4524886878 3239.0645927602))
((0 . "LWPOLYLINE") (100 . "AcDbEntity") (8 . "PLANTS") (62 . 94) (370 . 13) (100 . "AcDbPolyline") (90 . 2) (70 . 0)
(43 . 0.0) (10 4400.4524886878 478.882918552) (10 4415.5358597285 520.3619909502))
((0 . "LWPOLYLINE") (100 . "AcDbEntity") (8 . "PLANTS") (62 . 94) (370 . 13) (100 . "AcDbPolyline") (90 . 3) (70 . 0)
(43 . 0.0) (10 4407.9935520362 350.6787330317) (10 4400.6005656109 380.8455882353) (10 4400.4524886878 429.8642533937))
((0 . "LWPOLYLINE") (100 . "AcDbEntity") (8 . "PLANTS") (62 . 94) (370 . 13) (100 . "AcDbPolyline") (90 . 3) (70 . 0)
(43 . 0.0) (10 4400.4524886878 429.8642533937) (10 4419.3057692308 432.4368778281) (10 4434.3891402715 426.0944570136))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4430.6179864253 1074.6606334842 0.0) (10 4433.6341047316 1099.0549768049 0.0) (10 4400.7440280237
1109.2769009696 0.0) (10 4404.2236425339 1134.9915158371 0.0))
((0 . "LWPOLYLINE") (100 . "AcDbEntity") (8 . "PLANTS") (62 . 94) (370 . 13) (100 . "AcDbPolyline") (90 . 3) (70 . 0)
(43 . 0.0) (10 4407.9940045249 1195.3252262443) (10 4411.6100678733 1146.3037330317) (10 4404.2236425339
1134.9915158371))
((0 . "LWPOLYLINE") (100 . "AcDbEntity") (8 . "PLANTS") (62 . 94) (370 . 13) (100 . "AcDbPolyline") (90 . 3) (70 . 0)
(43 . 0.0) (10 4419.3057692308 6836.3496606335) (10 4426.8476244344 6874.0575791855) (10 4426.8476244344
6907.2398529412))
((0 . "LWPOLYLINE") (100 . "AcDbEntity") (8 . "PLANTS") (62 . 94) (370 . 13) (100 . "AcDbPolyline") (90 . 2) (70 . 0)
(43 . 0.0) (10 4447.5863122172 3608.5972850679) (10 4407.9935520362 3608.5972850679))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4419.3057692308 3540.7239819004 0.0) (10 4380.3727636188 3537.0901755814 0.0) (10 4399.1529633835
3592.6024150475 0.0) (10 4407.9935520362 3608.5972850679 0.0))
((0 . "LWPOLYLINE") (100 . "AcDbEntity") (8 . "PLANTS") (62 . 94) (370 . 13) (100 . "AcDbPolyline") (90 . 3) (70 . 0)
(43 . 0.0) (10 4415.5358597285 1048.2664027149) (10 4409.1914027149 1055.8135746606) (10 4407.9935520362
1070.8908371041))
((0 . "LWPOLYLINE") (100 . "AcDbEntity") (8 . "PLANTS") (62 . 94) (370 . 13) (100 . "AcDbPolyline") (90 . 2) (70 . 0)
(43 . 0.0) (10 4430.6179864253 1074.6606334842) (10 4407.9935520362 1070.8908371041))
((0 . "LWPOLYLINE") (100 . "AcDbEntity") (8 . "PLANTS") (62 . 94) (370 . 13) (100 . "AcDbPolyline") (90 . 2) (70 . 0)
(43 . 0.0) (10 4407.9935520362 350.6787330317) (10 4426.8480769231 350.6787330317))
((0 . "LWPOLYLINE") (100 . "AcDbEntity") (8 . "PLANTS") (62 . 94) (370 . 13) (100 . "AcDbPolyline") (90 . 3) (70 . 0)
(43 . 0.0) (10 4407.9935520362 350.6787330317) (10 4404.37760181 343.1314479638) (10 4407.9935520362 324.2845022624))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4426.8480769231 350.6787330317 0.0) (10 4431.113938612 338.7843371326 0.0) (10 4420.926553068
323.0104436321 0.0) (10 4407.9935520362 324.2845022624 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4483.4091628959 233.7867647059 0.0) (10 4461.0795636256 227.7430681834 0.0) (10 4420.4364317934
226.2631338996 0.0) (10 4407.9935520362 252.6385746606 0.0))
((0 . "LWPOLYLINE") (100 . "AcDbEntity") (8 . "PLANTS") (62 . 94) (370 . 13) (100 . "AcDbPolyline") (90 . 3) (70 . 0)
(43 . 0.0) (10 4407.9935520362 252.6385746606) (10 4433.3324660633 282.8054298643) (10 4464.554638009 335.596719457))
((0 . "LWPOLYLINE") (100 . "AcDbEntity") (8 . "PLANTS") (62 . 94) (370 . 13) (100 . "AcDbPolyline") (90 . 2) (70 . 0)
(43 . 0.0) (10 4407.9940045249 1195.3252262443) (10 4438.159841629 1195.3252262443))
((0 . "LWPOLYLINE") (100 . "AcDbEntity") (8 . "PLANTS") (62 . 94) (370 . 13) (100 . "AcDbPolyline") (90 . 2) (70 . 0)
(43 . 0.0) (10 4407.9940045249 1195.3252262443) (10 4407.9944092527 1253.0758032322))
((0 . "LWPOLYLINE") (100 . "AcDbEntity") (8 . "PLANTS") (62 . 94) (370 . 13) (100 . "AcDbPolyline") (90 . 2) (70 . 0)
(43 . 0.0) (10 4438.159841629 1230.8486425339) (10 4438.159841629 1195.3252262443))
((0 . "LWPOLYLINE") (100 . "AcDbEntity") (8 . "PLANTS") (62 . 94) (370 . 13) (100 . "AcDbPolyline") (90 . 3) (70 . 0)
(43 . 0.0) (10 4411.7647058824 1014.3297511312) (10 4434.3891402715 1006.9350678733) (10 4464.554638009
1006.7873303167))
((0 . "LWPOLYLINE") (100 . "AcDbEntity") (8 . "PLANTS") (62 . 94) (370 . 13) (100 . "AcDbPolyline") (90 . 2) (70 . 0)
(43 . 0.0) (10 4411.7647058824 1014.3297511312) (10 4415.5358597285 1048.2664027149))
((0 . "LWPOLYLINE") (100 . "AcDbEntity") (8 . "PLANTS") (62 . 94) (370 . 13) (100 . "AcDbPolyline") (90 . 2) (70 . 0)
(43 . 0.0) (10 4457.0135746606 4245.85260181) (10 4415.5358597285 4245.85260181))
((0 . "LWPOLYLINE") (100 . "AcDbEntity") (8 . "PLANTS") (62 . 94) (370 . 13) (100 . "AcDbPolyline") (90 . 2) (70 . 0)
(43 . 0.0) (10 4415.5358597285 4245.85260181) (10 4415.5358597285 4144.0426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4457.0135746607 4245.8526018099 0.0) (10 4469.0068853828 4212.9764864699 0.0) (10 4462.7611234818
4145.5817041569 0.0) (10 4415.5358597285 4144.0426470588 0.0))
((0 . "LWPOLYLINE") (100 . "AcDbEntity") (8 . "PLANTS") (62 . 94) (370 . 13) (100 . "AcDbPolyline") (90 . 2) (70 . 0)
(43 . 0.0) (10 4441.9302036199 1048.2664027149) (10 4415.5358597285 1048.2664027149))
((0 . "LWPOLYLINE") (100 . "AcDbEntity") (8 . "PLANTS") (62 . 94) (370 . 13) (100 . "AcDbPolyline") (90 . 3) (70 . 0)
(43 . 0.0) (10 4419.3057692308 6836.3496606335) (10 4426.8476244344 6806.1842760181) (10 4426.8476244344
6730.7692307692))
((0 . "LWPOLYLINE") (100 . "AcDbEntity") (8 . "PLANTS") (62 . 94) (370 . 13) (100 . "AcDbPolyline") (90 . 3) (70 . 0)
(43 . 0.0) (10 4419.3057692308 3540.7239819005) (10 4427.0020361991 3521.8769230769) (10 4441.9302036199
3510.5578054299))
((0 . "LWPOLYLINE") (100 . "AcDbEntity") (8 . "PLANTS") (62 . 94) (370 . 13) (100 . "AcDbPolyline") (90 . 2) (70 . 0)
(43 . 0.0) (10 4441.9302036199 3552.036199095) (10 4419.3057692308 3540.7239819005))
((0 . "LWPOLYLINE") (100 . "AcDbEntity") (8 . "PLANTS") (62 . 94) (370 . 13) (100 . "AcDbPolyline") (90 . 2) (70 . 0)
(43 . 0.0) (10 4423.0769230769 3819.7582579186) (10 4423.0769230769 3808.446040724))
((0 . "LWPOLYLINE") (100 . "AcDbEntity") (8 . "PLANTS") (62 . 94) (370 . 13) (100 . "AcDbPolyline") (90 . 2) (70 . 0)
(43 . 0.0) (10 4423.0769230769 3819.7582579186) (10 4457.0135746606 3838.6127828054))
((0 . "LWPOLYLINE") (100 . "AcDbEntity") (8 . "PLANTS") (62 . 94) (370 . 13) (100 . "AcDbPolyline") (90 . 2) (70 . 0)
(43 . 0.0) (10 4460.7847285068 3785.8216063348) (10 4423.0769230769 3808.446040724))
((0 . "LWPOLYLINE") (100 . "AcDbEntity") (8 . "PLANTS") (62 . 94) (370 . 13) (100 . "AcDbPolyline") (90 . 3) (70 . 0)
(43 . 0.0) (10 4423.0769230769 3457.7679864253) (10 4434.3891402715 3465.3089366516) (10 4438.1602941176
3463.4240950226))
((0 . "LWPOLYLINE") (100 . "AcDbEntity") (8 . "PLANTS") (62 . 94) (370 . 13) (100 . "AcDbPolyline") (90 . 2) (70 . 0)
(43 . 0.0) (10 4438.1602941176 3408.7478506787) (10 4426.8480769231 3404.9773755656))
((0 . "LWPOLYLINE") (100 . "AcDbEntity") (8 . "PLANTS") (62 . 94) (370 . 13) (100 . "AcDbPolyline") (90 . 3) (70 . 0)
(43 . 0.0) (10 4460.7847285068 392.1578054299) (10 4450.5279411765 384.4669683258) (10 4426.8480769231 350.6787330317))
((0 . "LWPOLYLINE") (100 . "AcDbEntity") (8 . "PLANTS") (62 . 94) (370 . 13) (100 . "AcDbPolyline") (90 . 2) (70 . 0)
(43 . 0.0) (10 4430.6179864253 3989.4415158371) (10 4453.2424208145 3981.9004524887))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4430.6179864254 3989.4415158371 0.0) (10 4425.6916821036 4034.7643314452 0.0) (10 4440.7612531851
4108.7552428872 0.0) (10 4498.4912895928 4106.334841629 0.0))
((0 . "LWPOLYLINE") (100 . "AcDbEntity") (8 . "PLANTS") (62 . 94) (370 . 13) (100 . "AcDbPolyline") (90 . 3) (70 . 0)
(43 . 0.0) (10 4441.9302036199 1048.2664027149) (10 4436.9686651584 1070.735520362) (10 4430.6179864253
1074.6606334842))
((0 . "LWPOLYLINE") (100 . "AcDbEntity") (8 . "PLANTS") (62 . 94) (370 . 13) (100 . "AcDbPolyline") (90 . 2) (70 . 0)
(43 . 0.0) (10 4436.2740950226 3239.0645927602) (10 4463.955072501 3239.0645927602))
((0 . "LWPOLYLINE") (100 . "AcDbEntity") (8 . "PLANTS") (62 . 94) (370 . 13) (100 . "AcDbPolyline") (90 . 2) (70 . 0)
(43 . 0.0) (10 4436.2740950226 3239.0645927602) (10 4436.0653615204 3235.2941176471))
((0 . "LWPOLYLINE") (100 . "AcDbEntity") (8 . "PLANTS") (62 . 94) (370 . 13) (100 . "AcDbPolyline") (90 . 2) (70 . 0)
(43 . 0.0) (10 4436.2740950226 3239.0645927602) (10 4438.1602941176 3273.0012443439))
((0 . "LWPOLYLINE") (100 . "AcDbEntity") (8 . "PLANTS") (62 . 94) (370 . 13) (100 . "AcDbPolyline") (90 . 2) (70 . 0)
(43 . 0.0) (10 4438.159841629 1195.3252262443) (10 4449.4725113122 1157.6159502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4502.2624434389 3404.9773755656 0.0) (10 4471.570329838 3415.7504867451 0.0) (10 4474.4093264016
3462.3871305337 0.0) (10 4438.1602941176 3463.4240950226 0.0))
((0 . "LWPOLYLINE") (100 . "AcDbEntity") (8 . "PLANTS") (62 . 94) (370 . 13) (100 . "AcDbPolyline") (90 . 2) (70 . 0)
(43 . 0.0) (10 4438.1602941176 3408.7478506787) (10 4438.1602941176 3463.4240950226))
((0 . "LWPOLYLINE") (100 . "AcDbEntity") (8 . "PLANTS") (62 . 94) (370 . 13) (100 . "AcDbPolyline") (90 . 2) (70 . 0)
(43 . 0.0) (10 4441.9302036199 3510.5578054299) (10 4438.1602941176 3463.4240950226))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4098894816) (40
. 1) (40 . 1) (40 . 1) (40 . 1) (10 4438.1602941177 3408.7478506787 0.0) (10 4450.8657350082 3396.3331656433 0.0) (10
4438.3095947424 3361.4515996861 0.0) (10 4448.4554229002 3324.1798036272 0.0) (10 4441.9302036199 3303.1674208145 0.0))
((0 . "LWPOLYLINE") (100 . "AcDbEntity") (8 . "PLANTS") (62 . 94) (370 . 13) (100 . "AcDbPolyline") (90 . 3) (70 . 0)
(43 . 0.0) (10 4438.1602941176 3273.0012443439) (10 4434.5437782805 3288.0847285068) (10 4441.9302036199
3303.1674208145))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4438.1602941176 3273.0012443439 0.0) (10 4483.1552796121 3266.7485331218 0.0) (10 4462.0988672894
3309.2809746909 0.0) (10 4441.9302036199 3303.1674208145 0.0))
((0 . "LWPOLYLINE") (100 . "AcDbEntity") (8 . "PLANTS") (62 . 94) (370 . 13) (100 . "AcDbPolyline") (90 . 3) (70 . 0)
(43 . 0.0) (10 4441.9302036199 3944.1926470588) (10 4446.8924208145 3933.0354072398) (10 4453.2424208145
3929.110520362))
((0 . "LWPOLYLINE") (100 . "AcDbEntity") (8 . "PLANTS") (62 . 94) (370 . 13) (100 . "AcDbPolyline") (90 . 3) (70 . 0)
(43 . 0.0) (10 4453.2424208145 3970.5882352941) (10 4446.8989819005 3966.6631221719) (10 4441.9302036199
3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4441.9302036199 3552.036199095 0.0) (10 4449.6152737364 3545.2614348493 0.0) (10 4462.9916437118
3514.5640856123 0.0) (10 4441.9302036199 3510.5578054299 0.0))
((0 . "LWPOLYLINE") (100 . "AcDbEntity") (8 . "PLANTS") (62 . 94) (370 . 13) (100 . "AcDbPolyline") (90 . 2) (70 . 0)
(43 . 0.0) (10 4447.5863122172 3608.5972850679) (10 4441.9302036199 3552.036199095))
((0 . "LWPOLYLINE") (100 . "AcDbEntity") (8 . "PLANTS") (62 . 94) (370 . 13) (100 . "AcDbPolyline") (90 . 2) (70 . 0)
(43 . 0.0) (10 4441.9302036199 1048.2664027149) (10 4464.554638009 1040.7239819005))
((0 . "LWPOLYLINE") (100 . "AcDbEntity") (8 . "PLANTS") (62 . 94) (370 . 13) (100 . "AcDbPolyline") (90 . 3) (70 . 0)
(43 . 0.0) (10 4447.5863122172 3608.5972850679) (10 4446.9058823529 3627.3027149321) (10 4464.554638009
3638.7627828054))
((0 . "LWPOLYLINE") (100 . "AcDbEntity") (8 . "PLANTS") (62 . 94) (370 . 13) (100 . "AcDbPolyline") (90 . 3) (70 . 0)
(43 . 0.0) (10 4479.6380090498 3623.6806561086) (10 4456.9462669683 3609.6536199095) (10 4447.5863122172
3608.5972850679))
((0 . "LWPOLYLINE") (100 . "AcDbEntity") (8 . "PLANTS") (62 . 94) (370 . 13) (100 . "AcDbPolyline") (90 . 2) (70 . 0)
(43 . 0.0) (10 4460.7847285068 275.2630090498) (10 4449.4725113122 267.7234162896))
((0 . "LWPOLYLINE") (100 . "AcDbEntity") (8 . "PLANTS") (62 . 94) (370 . 13) (100 . "AcDbPolyline") (90 . 2) (70 . 0)
(43 . 0.0) (10 4453.2424208145 3970.5882352941) (10 4453.2424208145 3981.9004524887))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4483.4091628959 4030.9204751131 0.0) (10 4462.8719271443 4020.0625734571 0.0) (10 4472.3140843671
3993.0232689075 0.0) (10 4453.2424208145 3981.9004524887 0.0))
((0 . "LWPOLYLINE") (100 . "AcDbEntity") (8 . "PLANTS") (62 . 94) (370 . 13) (100 . "AcDbPolyline") (90 . 2) (70 . 0)
(43 . 0.0) (10 4453.2424208145 3970.5882352941) (10 4483.4091628959 3955.5048642534))
((0 . "LWPOLYLINE") (100 . "AcDbEntity") (8 . "PLANTS") (62 . 94) (370 . 13) (100 . "AcDbPolyline") (90 . 2) (70 . 0)
(43 . 0.0) (10 4453.2424208145 3887.631561086) (10 4453.2424208145 3929.110520362))
((0 . "LWPOLYLINE") (100 . "AcDbEntity") (8 . "PLANTS") (62 . 94) (370 . 13) (100 . "AcDbPolyline") (90 . 2) (70 . 0)
(43 . 0.0) (10 4483.4091628959 3944.1926470588) (10 4453.2424208145 3929.110520362))
((0 . "LWPOLYLINE") (100 . "AcDbEntity") (8 . "PLANTS") (62 . 94) (370 . 13) (100 . "AcDbPolyline") (90 . 3) (70 . 0)
(43 . 0.0) (10 4457.0135746606 3883.8616515837) (10 4457.0135746606 3887.631561086) (10 4453.2424208145 3887.631561086))
((0 . "LWPOLYLINE") (100 . "AcDbEntity") (8 . "PLANTS") (62 . 94) (370 . 13) (100 . "AcDbPolyline") (90 . 2) (70 . 0)
(43 . 0.0) (10 4457.0135746606 3883.8616515837) (10 4453.2424208145 3887.631561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4457.0135746606 4245.85260181 0.0) (10 4461.1579605968 4265.0576903722 0.0) (10 4461.9733794893
4296.5382457308 0.0) (10 4483.4091628959 4306.1835972851 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4457.0135746606 3883.8616515837 0.0) (10 4503.6451046085 3911.2813006005 0.0) (10 4487.3839943162
3864.8674547159 0.0) (10 4509.8035067873 3857.4660633484 0.0))
((0 . "LWPOLYLINE") (100 . "AcDbEntity") (8 . "PLANTS") (62 . 94) (370 . 13) (100 . "AcDbPolyline") (90 . 2) (70 . 0)
(43 . 0.0) (10 4457.0135746606 3883.8616515837) (10 4457.0135746606 3838.6127828054))
((0 . "LWPOLYLINE") (100 . "AcDbEntity") (8 . "PLANTS") (62 . 94) (370 . 13) (100 . "AcDbPolyline") (90 . 2) (70 . 0)
(43 . 0.0) (10 4498.4912895928 3834.8416289593) (10 4457.0135746606 3838.6127828054))
((0 . "LWPOLYLINE") (100 . "AcDbEntity") (8 . "PLANTS") (62 . 94) (370 . 13) (100 . "AcDbPolyline") (90 . 2) (70 . 0)
(43 . 0.0) (10 4460.7847285068 3785.8216063348) (10 4494.7213800905 3789.592760181))
((0 . "LWPOLYLINE") (100 . "AcDbEntity") (8 . "PLANTS") (62 . 94) (370 . 13) (100 . "AcDbPolyline") (90 . 2) (70 . 0)
(43 . 0.0) (10 4460.7847285068 392.1578054299) (10 4490.9502262443 384.6153846154))
((0 . "LWPOLYLINE") (100 . "AcDbEntity") (8 . "PLANTS") (62 . 94) (370 . 13) (100 . "AcDbPolyline") (90 . 2) (70 . 0)
(43 . 0.0) (10 4460.7847285068 392.1578054299) (10 4464.554638009 403.4700226244))
((0 . "LWPOLYLINE") (100 . "AcDbEntity") (8 . "PLANTS") (62 . 94) (370 . 13) (100 . "AcDbPolyline") (90 . 2) (70 . 0)
(43 . 0.0) (10 4479.6380090498 3623.6806561086) (10 4464.554638009 3638.7627828054))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4464.5546380091 3638.7627828054 0.0) (10 4451.2775272775 3653.809155936 0.0) (10 4455.5727731959
3677.6652292172 0.0) (10 4468.3257918552 3691.553959276 0.0))
((0 . "LWPOLYLINE") (100 . "AcDbEntity") (8 . "PLANTS") (62 . 94) (370 . 13) (100 . "AcDbPolyline") (90 . 2) (70 . 0)
(43 . 0.0) (10 4464.554638009 1006.7873303167) (10 4464.554638009 1040.7239819005))
((0 . "LWPOLYLINE") (100 . "AcDbEntity") (8 . "PLANTS") (62 . 94) (370 . 13) (100 . "AcDbPolyline") (90 . 3) (70 . 0)
(43 . 0.0) (10 4502.2624434389 1089.7426470588) (10 4483.2607466063 1059.5786199095) (10 4464.554638009
1040.7239819005))
((0 . "LWPOLYLINE") (100 . "AcDbEntity") (8 . "PLANTS") (62 . 94) (370 . 13) (100 . "AcDbPolyline") (90 . 2) (70 . 0)
(43 . 0.0) (10 4472.0969457014 1003.0175339367) (10 4464.554638009 1006.7873303167))
((0 . "LWPOLYLINE") (100 . "AcDbEntity") (8 . "PLANTS") (62 . 94) (370 . 13) (100 . "AcDbPolyline") (90 . 2) (70 . 0)
(43 . 0.0) (10 4464.554638009 335.596719457) (10 4464.554638009 343.1363122172))
((0 . "LWPOLYLINE") (100 . "AcDbEntity") (8 . "PLANTS") (62 . 94) (370 . 13) (100 . "AcDbPolyline") (90 . 2) (70 . 0)
(43 . 0.0) (10 4464.554638009 335.596719457) (10 4483.4091628959 324.2845022624))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5312578787) (40
. 1) (40 . 1) (40 . 1) (40 . 1) (10 4536.1990950226 3729.2605203619 0.0) (10 4520.9778472631 3713.8895145316 0.0) (10
4481.5601794908 3748.3556392759 0.0) (10 4455.489164866 3709.4208520311 0.0) (10 4468.3257918552 3691.553959276 0.0))
((0 . "LWPOLYLINE") (100 . "AcDbEntity") (8 . "PLANTS") (62 . 94) (370 . 13) (100 . "AcDbPolyline") (90 . 3) (70 . 0)
(43 . 0.0) (10 4494.7213800905 3699.0950226244) (10 4487.1728506787 3691.707918552) (10 4468.3257918552 3691.553959276))
((0 . "LWPOLYLINE") (100 . "AcDbEntity") (8 . "PLANTS") (62 . 94) (370 . 13) (100 . "AcDbPolyline") (90 . 3) (70 . 0)
(43 . 0.0) (10 4513.5746606335 912.5197963801) (10 4487.1790723982 912.6668552036) (10 4468.3257918552 920.0593891403))
((0 . "LWPOLYLINE") (100 . "AcDbEntity") (8 . "PLANTS") (62 . 94) (370 . 13) (100 . "AcDbPolyline") (90 . 2) (70 . 0)
(43 . 0.0) (10 4475.8668552036 946.4564479638) (10 4468.3257918552 920.0593891403))
((0 . "LWPOLYLINE") (100 . "AcDbEntity") (8 . "PLANTS") (62 . 94) (370 . 13) (100 . "AcDbPolyline") (90 . 3) (70 . 0)
(43 . 0.0) (10 4475.8668552036 946.4564479638) (10 4472.2447963801 954.0036199095) (10 4472.0969457014 1003.0175339367))
((0 . "LWPOLYLINE") (100 . "AcDbEntity") (8 . "PLANTS") (62 . 94) (370 . 13) (100 . "AcDbPolyline") (90 . 3) (70 . 0)
(43 . 0.0) (10 4472.0969457014 1003.0175339367) (10 4509.8035067873 1011.7557692308) (10 4551.2824660633
1027.5254524887))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4506.0335972851 3465.3089366516 0.0) (10 4520.3337695611 3484.8170422195 0.0) (10 4489.9691371385
3494.1885758937 0.0) (10 4475.8668552036 3491.704638009 0.0))
((0 . "LWPOLYLINE") (100 . "AcDbEntity") (8 . "PLANTS") (62 . 94) (370 . 13) (100 . "AcDbPolyline") (90 . 3) (70 . 0)
(43 . 0.0) (10 4475.8668552036 946.4564479638) (10 4490.9502262443 956.563800905) (10 4513.5746606335 961.5384615385))
((0 . "LWPOLYLINE") (100 . "AcDbEntity") (8 . "PLANTS") (62 . 94) (370 . 13) (100 . "AcDbPolyline") (90 . 2) (70 . 0)
(43 . 0.0) (10 4479.6380090498 3623.6806561086) (10 4487.1790723982 3619.9095022624))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4479.6380090498 422.3218325792 0.0) (10 4495.2596763891 417.5223003499 0.0) (10 4496.4188355761
396.9189741635 0.0) (10 4490.9502262443 384.6153846154 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4479.7594197449 1200.1963218169 0.0) (10 4479.7581612098 1180.4830713691 0.0) (10 4474.5723881591
1145.3316581419 0.0) (10 4498.4912895928 1134.9915158371 0.0))
((0 . "LWPOLYLINE") (100 . "AcDbEntity") (8 . "PLANTS") (62 . 94) (370 . 13) (100 . "AcDbPolyline") (90 . 2) (70 . 0)
(43 . 0.0) (10 4483.4091628959 4306.1835972851) (10 4511.3067541112 4289.9830365389))
((0 . "LWPOLYLINE") (100 . "AcDbEntity") (8 . "PLANTS") (62 . 94) (370 . 13) (100 . "AcDbPolyline") (90 . 3) (70 . 0)
(43 . 0.0) (10 4516.6117951489 4277.1625206978) (10 4517.19739819 4264.7058823529) (10 4513.5746606335 4253.3936651584))
((0 . "LWPOLYLINE") (100 . "AcDbEntity") (8 . "PLANTS") (62 . 94) (370 . 13) (100 . "AcDbPolyline") (90 . 2) (70 . 0)
(43 . 0.0) (10 4486.7261876218 4349.3860722218) (10 4483.4091628959 4306.1835972851))
((0 . "LWPOLYLINE") (100 . "AcDbEntity") (8 . "PLANTS") (62 . 94) (370 . 13) (100 . "AcDbPolyline") (90 . 3) (70 . 0)
(43 . 0.0) (10 4498.4912895928 4027.149321267) (10 4487.1790723982 4027.149321267) (10 4483.4091628959 4030.9204751131))
((0 . "LWPOLYLINE") (100 . "AcDbEntity") (8 . "PLANTS") (62 . 94) (370 . 13) (100 . "AcDbPolyline") (90 . 3) (70 . 0)
(43 . 0.0) (10 4498.4912895928 4087.481561086) (10 4488.2295248869 4061.0859728507) (10 4483.4091628959
4030.9204751131))
((0 . "LWPOLYLINE") (100 . "AcDbEntity") (8 . "PLANTS") (62 . 94) (370 . 13) (100 . "AcDbPolyline") (90 . 2) (70 . 0)
(43 . 0.0) (10 4483.4091628959 3944.1926470588) (10 4483.4091628959 3955.5048642534))
((0 . "LWPOLYLINE") (100 . "AcDbEntity") (8 . "PLANTS") (62 . 94) (370 . 13) (100 . "AcDbPolyline") (90 . 2) (70 . 0)
(43 . 0.0) (10 4519.2307692308 3974.3593891403) (10 4483.4091628959 3955.5048642534))
((0 . "LWPOLYLINE") (100 . "AcDbEntity") (8 . "PLANTS") (62 . 94) (370 . 13) (100 . "AcDbPolyline") (90 . 3) (70 . 0)
(43 . 0.0) (10 4513.5746606335 3936.6515837104) (10 4498.4912895928 3937.7013574661) (10 4483.4091628959
3944.1926470588))
((0 . "LWPOLYLINE") (100 . "AcDbEntity") (8 . "PLANTS") (62 . 94) (370 . 13) (100 . "AcDbPolyline") (90 . 3) (70 . 0)
(43 . 0.0) (10 4483.4091628959 233.7867647059) (10 4502.2624434389 230.0141402715) (10 4547.5113122172 233.7867647059))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4483.4091628959 233.7867647059 0.0) (10 4477.347708775 261.0166103798 0.0) (10 4506.5555158097
273.3839246439 0.0) (10 4524.8868778281 282.8054298643 0.0))
((0 . "LWPOLYLINE") (100 . "AcDbEntity") (8 . "PLANTS") (62 . 94) (370 . 13) (100 . "AcDbPolyline") (90 . 2) (70 . 0)
(43 . 0.0) (10 4559.1971869479 3612.7075179659) (10 4487.1790723982 3619.9095022624))
((0 . "LWPOLYLINE") (100 . "AcDbEntity") (8 . "PLANTS") (62 . 94) (370 . 13) (100 . "AcDbPolyline") (90 . 2) (70 . 0)
(43 . 0.0) (10 4487.1790723982 3619.9095022624) (10 4487.1790723982 3582.2023755656))
((0 . "LWPOLYLINE") (100 . "AcDbEntity") (8 . "PLANTS") (62 . 94) (370 . 13) (100 . "AcDbPolyline") (90 . 2) (70 . 0)
(43 . 0.0) (10 4509.8035067873 3574.6606334842) (10 4487.1790723982 3582.2023755656))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4498.4912895928 3525.6412895928 0.0) (10 4482.1332830101 3535.6100675822 0.0) (10 4456.7646363914
3569.1593432618 0.0) (10 4487.1790723982 3582.2023755656 0.0))
((0 . "LWPOLYLINE") (100 . "AcDbEntity") (8 . "PLANTS") (62 . 94) (370 . 13) (100 . "AcDbPolyline") (90 . 3) (70 . 0)
(43 . 0.0) (10 4524.8868778281 365.7607466063) (10 4498.4981900452 374.3595022624) (10 4490.9502262443 384.6153846154))
((0 . "LWPOLYLINE") (100 . "AcDbEntity") (8 . "PLANTS") (62 . 94) (370 . 13) (100 . "AcDbPolyline") (90 . 3) (70 . 0)
(43 . 0.0) (10 4536.1990950226 3736.8028280543) (10 4520.0661764706 3774.3615384615) (10 4494.7213800905
3789.592760181))
((0 . "LWPOLYLINE") (100 . "AcDbEntity") (8 . "PLANTS") (62 . 94) (370 . 13) (100 . "AcDbPolyline") (90 . 3) (70 . 0)
(43 . 0.0) (10 4498.4912895928 3834.8416289593) (10 4494.8692307692 3823.5294117647) (10 4494.7213800905
3789.592760181))
((0 . "LWPOLYLINE") (100 . "AcDbEntity") (8 . "PLANTS") (62 . 94) (370 . 13) (100 . "AcDbPolyline") (90 . 2) (70 . 0)
(43 . 0.0) (10 4498.4912895928 4132.7304298643) (10 4498.4912895928 4106.334841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4513.5746606334 4253.3936651584 0.0) (10 4465.2644360785 4238.6129427357 0.0) (10 4473.8170893256
4164.4008390472 0.0) (10 4498.4912895927 4132.7304298643 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5989588502) (40
. 1) (40 . 1) (40 . 1) (40 . 1) (10 4513.5746606336 4253.3936651583 0.0) (10 4519.6067651324 4232.6431174501 0.0) (10
4523.6856903586 4184.5774659448 0.0) (10 4511.4905920441 4143.6379555909 0.0) (10 4498.4912895928 4132.7304298642 0.0))
((0 . "LWPOLYLINE") (100 . "AcDbEntity") (8 . "PLANTS") (62 . 94) (370 . 13) (100 . "AcDbPolyline") (90 . 2) (70 . 0)
(43 . 0.0) (10 4498.4912895928 4087.481561086) (10 4498.4912895928 4106.334841629))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4611493985) (40
. 1) (40 . 1) (40 . 1) (40 . 1) (10 4570.1357466063 4125.188122172 0.0) (10 4559.4907369762 4117.6262032312 0.0) (10
4543.9921149248 4091.4667057619 0.0) (10 4515.6889214978 4084.3589935491 0.0) (10 4498.4912895927 4087.481561086 0.0))
((0 . "LWPOLYLINE") (100 . "AcDbEntity") (8 . "PLANTS") (62 . 94) (370 . 13) (100 . "AcDbPolyline") (90 . 2) (70 . 0)
(43 . 0.0) (10 4498.4912895928 4027.149321267) (10 4519.2307692308 3974.3593891403))
((0 . "LWPOLYLINE") (100 . "AcDbEntity") (8 . "PLANTS") (62 . 94) (370 . 13) (100 . "AcDbPolyline") (90 . 3) (70 . 0)
(43 . 0.0) (10 4498.4912895928 4027.149321267) (10 4509.8041855204 4034.5364253394) (10 4551.2824660633
4038.4615384615))
((0 . "LWPOLYLINE") (100 . "AcDbEntity") (8 . "PLANTS") (62 . 94) (370 . 13) (100 . "AcDbPolyline") (90 . 2) (70 . 0)
(43 . 0.0) (10 4498.4912895928 3834.8416289593) (10 4509.8035067873 3857.4660633484))
((0 . "LWPOLYLINE") (100 . "AcDbEntity") (8 . "PLANTS") (62 . 94) (370 . 13) (100 . "AcDbPolyline") (90 . 3) (70 . 0)
(43 . 0.0) (10 4502.2624434389 1089.7426470588) (10 4498.6397058824 1101.0548642534) (10 4498.4912895928
1134.9915158371))
((0 . "LWPOLYLINE") (100 . "AcDbEntity") (8 . "PLANTS") (62 . 94) (370 . 13) (100 . "AcDbPolyline") (90 . 2) (70 . 0)
(43 . 0.0) (10 4513.5746606335 1165.1583710407) (10 4498.4912895928 1134.9915158371))
((0 . "LWPOLYLINE") (100 . "AcDbEntity") (8 . "PLANTS") (62 . 94) (370 . 13) (100 . "AcDbPolyline") (90 . 3) (70 . 0)
(43 . 0.0) (10 4573.3220498349 1131.2554364875) (10 4543.740158371 1105.8762443439) (10 4502.2624434389
1089.7426470588))
((0 . "LWPOLYLINE") (100 . "AcDbEntity") (8 . "PLANTS") (62 . 94) (370 . 13) (100 . "AcDbPolyline") (90 . 2) (70 . 0)
(43 . 0.0) (10 4536.1990950226 3861.2372171946) (10 4509.8035067873 3857.4660633484))
((0 . "LWPOLYLINE") (100 . "AcDbEntity") (8 . "PLANTS") (62 . 94) (370 . 13) (100 . "AcDbPolyline") (90 . 2) (70 . 0)
(43 . 0.0) (10 4513.5746606335 3936.6515837104) (10 4524.8868778281 3936.6515837104))
((0 . "LWPOLYLINE") (100 . "AcDbEntity") (8 . "PLANTS") (62 . 94) (370 . 13) (100 . "AcDbPolyline") (90 . 2) (70 . 0)
(43 . 0.0) (10 4513.5746606335 3936.6515837104) (10 4513.5746606335 3898.9437782805))
((0 . "LWPOLYLINE") (100 . "AcDbEntity") (8 . "PLANTS") (62 . 94) (370 . 13) (100 . "AcDbPolyline") (90 . 2) (70 . 0)
(43 . 0.0) (10 4513.5746606335 1165.1583710407) (10 4513.6174142392 1175.2483258738))
((0 . "LWPOLYLINE") (100 . "AcDbEntity") (8 . "PLANTS") (62 . 94) (370 . 13) (100 . "AcDbPolyline") (90 . 2) (70 . 0)
(43 . 0.0) (10 4513.5746606335 1165.1583710407) (10 4522.6369446056 1168.6023561301))
((0 . "LWPOLYLINE") (100 . "AcDbEntity") (8 . "PLANTS") (62 . 94) (370 . 13) (100 . "AcDbPolyline") (90 . 3) (70 . 0)
(43 . 0.0) (10 4513.5746606335 961.5384615385) (10 4517.3458144796 946.4564479638) (10 4513.5746606335 912.5197963801))
((0 . "LWPOLYLINE") (100 . "AcDbEntity") (8 . "PLANTS") (62 . 94) (370 . 13) (100 . "AcDbPolyline") (90 . 3) (70 . 0)
(43 . 0.0) (10 4513.5746606335 961.5384615385) (10 4528.6580316742 975.5648190045) (10 4551.2824660633 987.9326923077))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4513.5746606335 912.5197963801 0.0) (10 4536.7725214746 899.9048716336 0.0) (10 4573.3292598776
890.4755490354 0.0) (10 4592.7601809955 916.2895927602 0.0))
((0 . "LWPOLYLINE") (100 . "AcDbEntity") (8 . "PLANTS") (62 . 94) (370 . 13) (100 . "AcDbPolyline") (90 . 2) (70 . 0)
(43 . 0.0) (10 4581.4479638009 3966.817081448) (10 4519.2307692308 3974.3593891403))
((0 . "LWPOLYLINE") (100 . "AcDbEntity") (8 . "PLANTS") (62 . 94) (370 . 13) (100 . "AcDbPolyline") (90 . 2) (70 . 0)
(43 . 0.0) (10 4519.2307692308 3974.3593891403) (10 4524.8868778281 3936.6515837104))
((0 . "LWPOLYLINE") (100 . "AcDbEntity") (8 . "PLANTS") (62 . 94) (370 . 13) (100 . "AcDbPolyline") (90 . 2) (70 . 0)
(43 . 0.0) (10 4521.1157239819 3657.6173076923) (10 4521.1157239819 3665.1583710407))
((0 . "LWPOLYLINE") (100 . "AcDbEntity") (8 . "PLANTS") (62 . 94) (370 . 13) (100 . "AcDbPolyline") (90 . 2) (70 . 0)
(43 . 0.0) (10 4555.0523755656 3929.110520362) (10 4524.8868778281 3936.6515837104))
((0 . "LWPOLYLINE") (100 . "AcDbEntity") (8 . "PLANTS") (62 . 94) (370 . 13) (100 . "AcDbPolyline") (90 . 3) (70 . 0)
(43 . 0.0) (10 4524.8868778281 365.7607466063) (10 4532.2800904977 343.1363122172) (10 4528.6580316742 305.4298642534))
((0 . "LWPOLYLINE") (100 . "AcDbEntity") (8 . "PLANTS") (62 . 94) (370 . 13) (100 . "AcDbPolyline") (90 . 3) (70 . 0)
(43 . 0.0) (10 4524.8868778281 365.7607466063) (10 4554.0031674208 411.0096153846) (10 4581.4479638009 467.5707013575))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4547.5113122172 233.7867647059 0.0) (10 4532.5345108662 247.862456129 0.0) (10 4548.4127247508
272.6732819433 0.0) (10 4524.8868778281 282.8054298643 0.0))
((0 . "LWPOLYLINE") (100 . "AcDbEntity") (8 . "PLANTS") (62 . 94) (370 . 13) (100 . "AcDbPolyline") (90 . 2) (70 . 0)
(43 . 0.0) (10 4528.6580316742 305.4298642534) (10 4524.8868778281 282.8054298643))
((0 . "LWPOLYLINE") (100 . "AcDbEntity") (8 . "PLANTS") (62 . 94) (370 . 13) (100 . "AcDbPolyline") (90 . 2) (70 . 0)
(43 . 0.0) (10 4528.6580316742 305.4298642534) (10 4562.5946832579 305.4298642534))
((0 . "LWPOLYLINE") (100 . "AcDbEntity") (8 . "PLANTS") (62 . 94) (370 . 13) (100 . "AcDbPolyline") (90 . 2) (70 . 0)
(43 . 0.0) (10 4536.1990950226 3729.260520362) (10 4536.1990950226 3736.8028280543))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4592.7601809955 3746.2288461538 0.0) (10 4576.4124139056 3732.3968117771 0.0) (10 4553.9158967764
3747.0770587648 0.0) (10 4536.1990950226 3736.8028280543 0.0))
((0 . "LWPOLYLINE") (100 . "AcDbEntity") (8 . "PLANTS") (62 . 94) (370 . 13) (100 . "AcDbPolyline") (90 . 2) (70 . 0)
(43 . 0.0) (10 4536.1990950226 3729.260520362) (10 4563.3206388496 3658.0654888844))
((0 . "LWPOLYLINE") (100 . "AcDbEntity") (8 . "PLANTS") (62 . 94) (370 . 13) (100 . "AcDbPolyline") (90 . 2) (70 . 0)
(43 . 0.0) (10 4604.07239819 237.556561086) (10 4547.5113122172 233.7867647059))
((0 . "LWPOLYLINE") (100 . "AcDbEntity") (8 . "PLANTS") (62 . 94) (370 . 13) (100 . "AcDbPolyline") (90 . 3) (70 . 0)
(43 . 0.0) (10 4573.9069004525 4019.6082579186) (10 4555.2073529412 4027.303959276) (10 4551.2824660633
4038.4615384615))
((0 . "LWPOLYLINE") (100 . "AcDbEntity") (8 . "PLANTS") (62 . 94) (370 . 13) (100 . "AcDbPolyline") (90 . 3) (70 . 0)
(43 . 0.0) (10 4581.4479638009 4076.1693438914) (10 4556.2571266968 4060.9378959276) (10 4551.2824660633
4038.4615384615))
((0 . "LWPOLYLINE") (100 . "AcDbEntity") (8 . "PLANTS") (62 . 94) (370 . 13) (100 . "AcDbPolyline") (90 . 3) (70 . 0)
(43 . 0.0) (10 4592.7601809955 1018.0995475113) (10 4566.3645927602 1018.2541855204) (10 4551.2824660633
1027.5254524887))
((0 . "LWPOLYLINE") (100 . "AcDbEntity") (8 . "PLANTS") (62 . 94) (370 . 13) (100 . "AcDbPolyline") (90 . 2) (70 . 0)
(43 . 0.0) (10 4551.2824660633 987.9326923077) (10 4551.2824660633 1027.5254524887))
((0 . "LWPOLYLINE") (100 . "AcDbEntity") (8 . "PLANTS") (62 . 94) (370 . 13) (100 . "AcDbPolyline") (90 . 2) (70 . 0)
(43 . 0.0) (10 4551.2824660633 1027.5254524887) (10 4555.0523755656 1052.036199095))
((0 . "LWPOLYLINE") (100 . "AcDbEntity") (8 . "PLANTS") (62 . 94) (370 . 13) (100 . "AcDbPolyline") (90 . 2) (70 . 0)
(43 . 0.0) (10 4551.2824660633 987.9326923077) (10 4577.6768099548 980.3930995475))
((0 . "LWPOLYLINE") (100 . "AcDbEntity") (8 . "PLANTS") (62 . 94) (370 . 13) (100 . "AcDbPolyline") (90 . 3) (70 . 0)
(43 . 0.0) (10 4585.2191176471 3921.5682126697) (10 4566.3652714932 3921.7231900452) (10 4555.0523755656
3929.110520362))
((0 . "LWPOLYLINE") (100 . "AcDbEntity") (8 . "PLANTS") (62 . 94) (370 . 13) (100 . "AcDbPolyline") (90 . 2) (70 . 0)
(43 . 0.0) (10 4555.0523755656 3929.110520362) (10 4562.5946832579 3944.1926470588))
((0 . "LWPOLYLINE") (100 . "AcDbEntity") (8 . "PLANTS") (62 . 94) (370 . 13) (100 . "AcDbPolyline") (90 . 2) (70 . 0)
(43 . 0.0) (10 4573.9069004525 1052.036199095) (10 4555.0523755656 1052.036199095))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4595.5579387457 1114.87109729 0.0) (10 4585.596176593 1088.5730033895 0.0) (10 4542.7096799567
1093.8356586534 0.0) (10 4555.0523755656 1052.036199095 0.0))
((0 . "LWPOLYLINE") (100 . "AcDbEntity") (8 . "PLANTS") (62 . 94) (370 . 13) (100 . "AcDbPolyline") (90 . 2) (70 . 0)
(43 . 0.0) (10 4592.7601809955 3876.3193438914) (10 4558.8235294118 3865.0071266968))
((0 . "LWPOLYLINE") (100 . "AcDbEntity") (8 . "PLANTS") (62 . 94) (370 . 13) (100 . "AcDbPolyline") (90 . 3) (70 . 0)
(43 . 0.0) (10 4570.1357466063 3951.7349547511) (10 4566.3645927602 3951.7349547511) (10 4562.5946832579
3944.1926470588))
((0 . "LWPOLYLINE") (100 . "AcDbEntity") (8 . "PLANTS") (62 . 94) (370 . 13) (100 . "AcDbPolyline") (90 . 3) (70 . 0)
(43 . 0.0) (10 4570.1357466063 3951.7349547511) (10 4570.1357466063 3947.963800905) (10 4562.5946832579
3944.1926470588))
((0 . "LWPOLYLINE") (100 . "AcDbEntity") (8 . "PLANTS") (62 . 94) (370 . 13) (100 . "AcDbPolyline") (90 . 2) (70 . 0)
(43 . 0.0) (10 4566.3645927602 286.5752262443) (10 4562.5946832579 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4622.925678733 350.6787330317 0.0) (10 4594.5389569674 352.3525848063 0.0) (10 4575.8749660003
325.7619642921 0.0) (10 4562.5946832579 305.4298642534 0.0))
((0 . "LWPOLYLINE") (100 . "AcDbEntity") (8 . "PLANTS") (62 . 94) (370 . 13) (100 . "AcDbPolyline") (90 . 2) (70 . 0)
(43 . 0.0) (10 4570.1357466063 4147.8125565611) (10 4570.1357466063 4125.1881221719))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4570.1357466063 4125.1881221719 0.0) (10 4587.1373993539 4115.76757824 0.0) (10 4591.5915196088
4091.5454301191 0.0) (10 4581.4479638009 4076.1693438914 0.0))
((0 . "LWPOLYLINE") (100 . "AcDbEntity") (8 . "PLANTS") (62 . 94) (370 . 13) (100 . "AcDbPolyline") (90 . 2) (70 . 0)
(43 . 0.0) (10 4581.4479638009 3959.2760180995) (10 4570.1357466063 3951.7349547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4570.1357466063 365.7607466063 0.0) (10 4596.3387714726 390.1359234259 0.0) (10 4592.1794688557
434.1768494303 0.0) (10 4630.4679864253 448.7188914027 0.0))
((0 . "LWPOLYLINE") (100 . "AcDbEntity") (8 . "PLANTS") (62 . 94) (370 . 13) (100 . "AcDbPolyline") (90 . 2) (70 . 0)
(43 . 0.0) (10 4573.9069004525 4019.6082579186) (10 4577.6768099548 4012.0659502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4581.4479638009 4076.1693438914 0.0) (10 4592.2166926421 4059.0000102649 0.0) (10 4587.9285981009
4033.7749951595 0.0) (10 4573.9069004525 4019.6082579186 0.0))
((0 . "LWPOLYLINE") (100 . "AcDbEntity") (8 . "PLANTS") (62 . 94) (370 . 13) (100 . "AcDbPolyline") (90 . 2) (70 . 0)
(43 . 0.0) (10 4592.7601809955 1018.0995475113) (10 4573.9069004525 1052.036199095))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4573.9069004525 1052.036199095 0.0) (10 4587.6093809158 1073.8461702871 0.0) (10 4617.9232591153
1082.8694781512 0.0) (10 4641.7802036199 1074.6606334842 0.0))
((0 . "LWPOLYLINE") (100 . "AcDbEntity") (8 . "PLANTS") (62 . 94) (370 . 13) (100 . "AcDbPolyline") (90 . 2) (70 . 0)
(43 . 0.0) (10 4573.9069004525 961.5384615385) (10 4577.6768099548 980.3930995475))
((0 . "LWPOLYLINE") (100 . "AcDbEntity") (8 . "PLANTS") (62 . 94) (370 . 13) (100 . "AcDbPolyline") (90 . 2) (70 . 0)
(43 . 0.0) (10 4581.4479638009 3966.817081448) (10 4577.6768099548 4012.0659502262))
((0 . "LWPOLYLINE") (100 . "AcDbEntity") (8 . "PLANTS") (62 . 94) (370 . 13) (100 . "AcDbPolyline") (90 . 2) (70 . 0)
(43 . 0.0) (10 4649.3212669683 4013.9521493213) (10 4577.6768099548 4012.0659502262))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3895802436) (40
. 1) (40 . 1) (40 . 1) (40 . 1) (10 4683.2579185521 965.3082579185 0.0) (10 4675.5848823377 942.5332932476 0.0) (10
4640.6828084788 939.0173986555 0.0) (10 4602.1992874048 985.3968509968 0.0) (10 4577.6768099548 980.3930995475 0.0))
((0 . "LWPOLYLINE") (100 . "AcDbEntity") (8 . "PLANTS") (62 . 94) (370 . 13) (100 . "AcDbPolyline") (90 . 3) (70 . 0)
(43 . 0.0) (10 4592.7601809955 916.2895927602) (10 4582.504638009 927.6018099548) (10 4577.6768099548 942.6838235294))
((0 . "LWPOLYLINE") (100 . "AcDbEntity") (8 . "PLANTS") (62 . 94) (370 . 13) (100 . "AcDbPolyline") (90 . 2) (70 . 0)
(43 . 0.0) (10 4581.4479638009 3966.817081448) (10 4581.4479638009 3959.2760180995))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4585.2191176471 3921.5682126697 0.0) (10 4592.2155408587 3932.6669343716 0.0) (10 4595.0467189913
3952.012194969 0.0) (10 4581.4479638009 3959.2760180995 0.0))
((0 . "LWPOLYLINE") (100 . "AcDbEntity") (8 . "PLANTS") (62 . 94) (370 . 13) (100 . "AcDbPolyline") (90 . 3) (70 . 0)
(43 . 0.0) (10 4592.7601809955 3876.3193438914) (10 4585.3669683258 3898.9437782805) (10 4585.2191176471
3921.5682126697))
((0 . "LWPOLYLINE") (100 . "AcDbEntity") (8 . "PLANTS") (62 . 94) (370 . 13) (100 . "AcDbPolyline") (90 . 2) (70 . 0)
(43 . 0.0) (10 4592.7601809955 3876.3193438914) (10 4600.3012443439 3876.3193438914))
((0 . "LWPOLYLINE") (100 . "AcDbEntity") (8 . "PLANTS") (62 . 94) (370 . 13) (100 . "AcDbPolyline") (90 . 2) (70 . 0)
(43 . 0.0) (10 4594.5199974801 3733.0316742081) (10 4592.7601809955 3746.2288461538))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4611.6134615385 3823.5294117647 0.0) (10 4582.1684539727 3815.7143339929 0.0) (10 4603.2690552649
3751.3620658862 0.0) (10 4592.7601809955 3746.2288461538 0.0))
((0 . "LWPOLYLINE") (100 . "AcDbEntity") (8 . "PLANTS") (62 . 94) (370 . 13) (100 . "AcDbPolyline") (90 . 2) (70 . 0)
(43 . 0.0) (10 4592.7601809955 3746.2288461538) (10 4626.6968325792 3748.1150452489))
((0 . "LWPOLYLINE") (100 . "AcDbEntity") (8 . "PLANTS") (62 . 94) (370 . 13) (100 . "AcDbPolyline") (90 . 3) (70 . 0)
(43 . 0.0) (10 4592.7601809955 1018.0995475113) (10 4630.4679864253 1006.9350678733) (10 4660.6334841629
1006.7873303167))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4713.4234162896 916.2895927601 0.0) (10 4684.1776269907 880.3135925701 0.0) (10 4627.5481776262
901.9366472555 0.0) (10 4592.7601809955 916.2895927602 0.0))
((0 . "LWPOLYLINE") (100 . "AcDbEntity") (8 . "PLANTS") (62 . 94) (370 . 13) (100 . "AcDbPolyline") (90 . 2) (70 . 0)
(43 . 0.0) (10 4600.3012443439 3876.3193438914) (10 4611.6134615385 3823.5294117647))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4754.9023755656 3865.0071266968 0.0) (10 4720.7590175596 3918.1276367969 0.0) (10 4645.8824827118
3903.1487618263 0.0) (10 4600.3012443439 3876.3193438914 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4698.3412895928 260.1809954751 0.0) (10 4680.5538820212 224.2530105574 0.0) (10 4635.279229927
225.1675815254 0.0) (10 4604.07239819 237.556561086 0.0))
((0 . "LWPOLYLINE") (100 . "AcDbEntity") (8 . "PLANTS") (62 . 94) (370 . 13) (100 . "AcDbPolyline") (90 . 3) (70 . 0)
(43 . 0.0) (10 4604.07239819 237.556561086) (10 4604.2204751131 267.7234162896) (10 4611.6134615385 297.8874434389))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4611.6134615385 3823.5294117647 0.0) (10 4633.0408477641 3819.524258661 0.0) (10 4648.0742519238
3798.3088733604 0.0) (10 4653.0924208145 3778.2805429864 0.0))
((0 . "LWPOLYLINE") (100 . "AcDbEntity") (8 . "PLANTS") (62 . 94) (370 . 13) (100 . "AcDbPolyline") (90 . 3) (70 . 0)
(43 . 0.0) (10 4656.8623303167 290.3478506787) (10 4641.7802036199 281.1476244344) (10 4611.6134615385 297.8874434389))
((0 . "LWPOLYLINE") (100 . "AcDbEntity") (8 . "PLANTS") (62 . 94) (370 . 13) (100 . "AcDbPolyline") (90 . 2) (70 . 0)
(43 . 0.0) (10 4615.3846153846 312.9722850679) (10 4611.6134615385 297.8874434389))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4622.925678733 350.6787330317 0.0) (10 4624.4336931354 324.4248155916 0.0) (10 4663.3138351699
318.0128905707 0.0) (10 4656.8623303167 290.3478506787 0.0))
((0 . "LWPOLYLINE") (100 . "AcDbEntity") (8 . "PLANTS") (62 . 94) (370 . 13) (100 . "AcDbPolyline") (90 . 2) (70 . 0)
(43 . 0.0) (10 4622.925678733 350.6787330317) (10 4638.0090497738 361.9909502262))
((0 . "LWPOLYLINE") (100 . "AcDbEntity") (8 . "PLANTS") (62 . 94) (370 . 13) (100 . "AcDbPolyline") (90 . 2) (70 . 0)
(43 . 0.0) (10 4638.0090497738 3733.0316742081) (10 4626.6968325792 3748.1150452489))
((0 . "LWPOLYLINE") (100 . "AcDbEntity") (8 . "PLANTS") (62 . 94) (370 . 13) (100 . "AcDbPolyline") (90 . 3) (70 . 0)
(43 . 0.0) (10 4653.0924208145 3778.2805429864) (10 4635.2883484163 3763.049321267) (10 4626.6968325792
3748.1150452489))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4705.8823529411 309.1996606334 0.0) (10 4659.3837183985 339.7090742173 0.0) (10 4678.8118141861
416.4643045263 0.0) (10 4630.4679864253 448.7188914027 0.0))
((0 . "LWPOLYLINE") (100 . "AcDbEntity") (8 . "PLANTS") (62 . 94) (370 . 13) (100 . "AcDbPolyline") (90 . 2) (70 . 0)
(43 . 0.0) (10 4632.4858932895 454.7900029846) (10 4630.4679864253 448.7188914027))
((0 . "LWPOLYLINE") (100 . "AcDbEntity") (8 . "PLANTS") (62 . 94) (370 . 13) (100 . "AcDbPolyline") (90 . 3) (70 . 0)
(43 . 0.0) (10 4638.0090497738 3947.963800905) (10 4642.8294117647 3959.1213800905) (10 4649.3212669683
3963.0471719457))
((0 . "LWPOLYLINE") (100 . "AcDbEntity") (8 . "PLANTS") (62 . 94) (370 . 13) (100 . "AcDbPolyline") (90 . 3) (70 . 0)
(43 . 0.0) (10 4638.0090497738 3733.0316742081) (10 4656.8623303167 3741.7705882353) (10 4675.7168552036
3759.4272624434))
((0 . "LWPOLYLINE") (100 . "AcDbEntity") (8 . "PLANTS") (62 . 94) (370 . 13) (100 . "AcDbPolyline") (90 . 2) (70 . 0)
(43 . 0.0) (10 4646.0009667074 1121.3581537471) (10 4649.3212669683 1097.2850678733))
((0 . "LWPOLYLINE") (100 . "AcDbEntity") (8 . "PLANTS") (62 . 94) (370 . 13) (100 . "AcDbPolyline") (90 . 3) (70 . 0)
(43 . 0.0) (10 4691.9371519875 1135.3387318758) (10 4698.3412895928 1128.5075791855) (10 4717.1945701357
1123.6792986425))
((0 . "LWPOLYLINE") (100 . "AcDbEntity") (8 . "PLANTS") (62 . 94) (370 . 13) (100 . "AcDbPolyline") (90 . 3) (70 . 0)
(43 . 0.0) (10 4660.6334841629 1044.4937782805) (10 4646.7483031674 1055.8059954751) (10 4641.7802036199
1074.6606334842))
((0 . "LWPOLYLINE") (100 . "AcDbEntity") (8 . "PLANTS") (62 . 94) (370 . 13) (100 . "AcDbPolyline") (90 . 2) (70 . 0)
(43 . 0.0) (10 4641.7802036199 1074.6606334842) (10 4649.3212669683 1097.2850678733))
((0 . "LWPOLYLINE") (100 . "AcDbEntity") (8 . "PLANTS") (62 . 94) (370 . 13) (100 . "AcDbPolyline") (90 . 2) (70 . 0)
(43 . 0.0) (10 4649.3212669683 4013.9521493213) (10 4649.3212669683 3963.0471719457))
((0 . "LWPOLYLINE") (100 . "AcDbEntity") (8 . "PLANTS") (62 . 94) (370 . 13) (100 . "AcDbPolyline") (90 . 2) (70 . 0)
(43 . 0.0) (10 4649.3212669683 4013.9521493213) (10 4650.6178764549 4045.7154451525))
((0 . "LWPOLYLINE") (100 . "AcDbEntity") (8 . "PLANTS") (62 . 94) (370 . 13) (100 . "AcDbPolyline") (90 . 2) (70 . 0)
(43 . 0.0) (10 4649.3212669683 4013.9521493213) (10 4675.7168552036 4015.8371040724))
((0 . "LWPOLYLINE") (100 . "AcDbEntity") (8 . "PLANTS") (62 . 94) (370 . 13) (100 . "AcDbPolyline") (90 . 2) (70 . 0)
(43 . 0.0) (10 4649.3212669683 3963.0471719457) (10 4709.6535067873 3932.8804298643))
((0 . "LWPOLYLINE") (100 . "AcDbEntity") (8 . "PLANTS") (62 . 94) (370 . 13) (100 . "AcDbPolyline") (90 . 2) (70 . 0)
(43 . 0.0) (10 4660.6334841629 1093.5152714932) (10 4649.3212669683 1097.2850678733))
((0 . "LWPOLYLINE") (100 . "AcDbEntity") (8 . "PLANTS") (62 . 94) (370 . 13) (100 . "AcDbPolyline") (90 . 3) (70 . 0)
(43 . 0.0) (10 4675.7168552036 3759.4272624434) (10 4668.0266968326 3773.453280543) (10 4653.0924208145
3778.2805429864))
((0 . "LWPOLYLINE") (100 . "AcDbEntity") (8 . "PLANTS") (62 . 94) (370 . 13) (100 . "AcDbPolyline") (90 . 3) (70 . 0)
(43 . 0.0) (10 4698.3412895928 260.1809954751) (10 4675.7168552036 282.6507918552) (10 4656.8623303167 290.3478506787))
((0 . "LWPOLYLINE") (100 . "AcDbEntity") (8 . "PLANTS") (62 . 94) (370 . 13) (100 . "AcDbPolyline") (90 . 2) (70 . 0)
(43 . 0.0) (10 4660.6334841629 1006.7873303167) (10 4660.6334841629 1044.4937782805))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4717.1945701357 1070.8908371041 0.0) (10 4678.9936800001 1093.2313899665 0.0) (10 4693.5231053629
1035.5473954766 0.0) (10 4660.6334841629 1044.4937782805 0.0))
((0 . "LWPOLYLINE") (100 . "AcDbEntity") (8 . "PLANTS") (62 . 94) (370 . 13) (100 . "AcDbPolyline") (90 . 3) (70 . 0)
(43 . 0.0) (10 4683.257918552 965.3082579186) (10 4673.0023755656 976.6204751131) (10 4660.6334841629 1006.7873303167))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4758.6722850679 3932.8804298643 0.0) (10 4706.0559299851 3934.9866989723 0.0) (10 4734.8821050663
4013.8156622902 0.0) (10 4675.7168552036 4015.8371040724 0.0))
((0 . "LWPOLYLINE") (100 . "AcDbEntity") (8 . "PLANTS") (62 . 94) (370 . 13) (100 . "AcDbPolyline") (90 . 2) (70 . 0)
(43 . 0.0) (10 4675.7168552036 4015.8371040724) (10 4702.111199095 4046.00260181))
((0 . "LWPOLYLINE") (100 . "AcDbEntity") (8 . "PLANTS") (62 . 94) (370 . 13) (100 . "AcDbPolyline") (90 . 3) (70 . 0)
(43 . 0.0) (10 4675.7168552036 3759.4272624434) (10 4686.8806561086 3758.2225113122) (10 4707.3082615568
3733.0316742081))
((0 . "LWPOLYLINE") (100 . "AcDbEntity") (8 . "PLANTS") (62 . 94) (370 . 13) (100 . "AcDbPolyline") (90 . 2) (70 . 0)
(43 . 0.0) (10 4683.257918552 965.3082579186) (10 4702.111199095 965.3082579186))
((0 . "LWPOLYLINE") (100 . "AcDbEntity") (8 . "PLANTS") (62 . 94) (370 . 13) (100 . "AcDbPolyline") (90 . 2) (70 . 0)
(43 . 0.0) (10 4698.3412895928 260.1809954751) (10 4709.6535067873 260.1809954751))
((0 . "LWPOLYLINE") (100 . "AcDbEntity") (8 . "PLANTS") (62 . 94) (370 . 13) (100 . "AcDbPolyline") (90 . 3) (70 . 0)
(43 . 0.0) (10 4702.111199095 965.3082579186) (10 4702.2596153846 950.2262443439) (10 4713.4234162896 916.2895927602))
((0 . "LWPOLYLINE") (100 . "AcDbEntity") (8 . "PLANTS") (62 . 94) (370 . 13) (100 . "AcDbPolyline") (90 . 2) (70 . 0)
(43 . 0.0) (10 4713.4234162896 987.9326923077) (10 4702.111199095 965.3082579186))
((0 . "LWPOLYLINE") (100 . "AcDbEntity") (8 . "PLANTS") (62 . 94) (370 . 13) (100 . "AcDbPolyline") (90 . 3) (70 . 0)
(43 . 0.0) (10 4705.8823529412 309.1996606335) (10 4706.0369909502 290.3478506787) (10 4713.4234162896 279.0356334842))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4758.6722850679 437.4066742081 0.0) (10 4719.241174054 404.5015001569 0.0) (10 4743.1410826214
340.8031480599 0.0) (10 4705.8823529412 309.1996606335 0.0))
((0 . "LWPOLYLINE") (100 . "AcDbEntity") (8 . "PLANTS") (62 . 94) (370 . 13) (100 . "AcDbPolyline") (90 . 2) (70 . 0)
(43 . 0.0) (10 4720.5916728361 1144.0596730036) (10 4717.1945701357 1123.6792986425))
((0 . "LWPOLYLINE") (100 . "AcDbEntity") (8 . "PLANTS") (62 . 94) (370 . 13) (100 . "AcDbPolyline") (90 . 3) (70 . 0)
(43 . 0.0) (10 4709.6535067873 260.1809954751) (10 4728.5067873303 238.7614253394) (10 4781.296719457 237.556561086))
((0 . "LWPOLYLINE") (100 . "AcDbEntity") (8 . "PLANTS") (62 . 94) (370 . 13) (100 . "AcDbPolyline") (90 . 2) (70 . 0)
(43 . 0.0) (10 4713.4234162896 279.0356334842) (10 4709.6535067873 260.1809954751))
((0 . "LWPOLYLINE") (100 . "AcDbEntity") (8 . "PLANTS") (62 . 94) (370 . 13) (100 . "AcDbPolyline") (90 . 2) (70 . 0)
(43 . 0.0) (10 4724.7356334842 4038.4615384615) (10 4713.4234162896 4053.5449095023))
((0 . "LWPOLYLINE") (100 . "AcDbEntity") (8 . "PLANTS") (62 . 94) (370 . 13) (100 . "AcDbPolyline") (90 . 3) (70 . 0)
(43 . 0.0) (10 4722.2515837104 3733.0316742081) (10 4731.0797511312 3740.5727375566) (10 4743.590158371
3785.8216063348))
((0 . "LWPOLYLINE") (100 . "AcDbEntity") (8 . "PLANTS") (62 . 94) (370 . 13) (100 . "AcDbPolyline") (90 . 3) (70 . 0)
(43 . 0.0) (10 4713.4234162896 987.9326923077) (10 4703.4702488688 1025.6419683258) (10 4720.9657239819
1040.7239819005))
((0 . "LWPOLYLINE") (100 . "AcDbEntity") (8 . "PLANTS") (62 . 94) (370 . 13) (100 . "AcDbPolyline") (90 . 3) (70 . 0)
(43 . 0.0) (10 4713.4234162896 987.9326923077) (10 4732.2772624434 992.6125565611) (10 4743.590158371 1003.0175339367))
((0 . "LWPOLYLINE") (100 . "AcDbEntity") (8 . "PLANTS") (62 . 94) (370 . 13) (100 . "AcDbPolyline") (90 . 2) (70 . 0)
(43 . 0.0) (10 4720.9657239819 916.2895927602) (10 4713.4234162896 916.2895927602))
((0 . "LWPOLYLINE") (100 . "AcDbEntity") (8 . "PLANTS") (62 . 94) (370 . 13) (100 . "AcDbPolyline") (90 . 3) (70 . 0)
(43 . 0.0) (10 4713.4234162896 279.0356334842) (10 4739.6709276018 294.2722850679) (10 4758.6722850679 335.596719457))
((0 . "LWPOLYLINE") (100 . "AcDbEntity") (8 . "PLANTS") (62 . 94) (370 . 13) (100 . "AcDbPolyline") (90 . 3) (70 . 0)
(43 . 0.0) (10 4717.1945701357 1070.8908371041) (10 4720.9657239819 1097.2850678733) (10 4717.1945701357
1123.6792986425))
((0 . "LWPOLYLINE") (100 . "AcDbEntity") (8 . "PLANTS") (62 . 94) (370 . 13) (100 . "AcDbPolyline") (90 . 3) (70 . 0)
(43 . 0.0) (10 4717.1945701357 1070.8908371041) (10 4720.8173076923 1063.3415158371) (10 4720.9657239819
1040.7239819005))
((0 . "LWPOLYLINE") (100 . "AcDbEntity") (8 . "PLANTS") (62 . 94) (370 . 13) (100 . "AcDbPolyline") (90 . 2) (70 . 0)
(43 . 0.0) (10 4736.0478506787 1040.7239819005) (10 4720.9657239819 1040.7239819005))
((0 . "LWPOLYLINE") (100 . "AcDbEntity") (8 . "PLANTS") (62 . 94) (370 . 13) (100 . "AcDbPolyline") (90 . 3) (70 . 0)
(43 . 0.0) (10 4720.9657239819 916.2895927602) (10 4736.0478506787 905.1320135747) (10 4788.8390271493 908.7471719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4773.7556561086 961.5384615385 0.0) (10 4766.0123400564 933.9552857053 0.0) (10 4731.9093863034
941.1159844968 0.0) (10 4720.9657239819 916.2895927602 0.0))
((0 . "LWPOLYLINE") (100 . "AcDbEntity") (8 . "PLANTS") (62 . 94) (370 . 13) (100 . "AcDbPolyline") (90 . 3) (70 . 0)
(43 . 0.0) (10 4736.0478506787 1040.7239819005) (10 4733.4752262443 1025.6419683258) (10 4743.590158371
1003.0175339367))
((0 . "LWPOLYLINE") (100 . "AcDbEntity") (8 . "PLANTS") (62 . 94) (370 . 13) (100 . "AcDbPolyline") (90 . 2) (70 . 0)
(43 . 0.0) (10 4766.2145927602 1044.4937782805) (10 4736.0478506787 1040.7239819005))
((0 . "LWPOLYLINE") (100 . "AcDbEntity") (8 . "PLANTS") (62 . 94) (370 . 13) (100 . "AcDbPolyline") (90 . 2) (70 . 0)
(43 . 0.0) (10 4743.590158371 3785.8216063348) (10 4777.5268099548 3785.8216063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4754.9023755656 3857.4660633484 0.0) (10 4738.5897545638 3844.992194694 0.0) (10 4703.0959147142
3793.2517982716 0.0) (10 4743.590158371 3785.8216063348 0.0))
((0 . "LWPOLYLINE") (100 . "AcDbEntity") (8 . "PLANTS") (62 . 94) (370 . 13) (100 . "AcDbPolyline") (90 . 2) (70 . 0)
(43 . 0.0) (10 4743.590158371 1003.0175339367) (10 4762.443438914 1003.0175339367))
((0 . "LWPOLYLINE") (100 . "AcDbEntity") (8 . "PLANTS") (62 . 94) (370 . 13) (100 . "AcDbPolyline") (90 . 2) (70 . 0)
(43 . 0.0) (10 4754.9023755656 3857.4660633484) (10 4754.9023755656 3865.0071266968))
((0 . "LWPOLYLINE") (100 . "AcDbEntity") (8 . "PLANTS") (62 . 94) (370 . 13) (100 . "AcDbPolyline") (90 . 3) (70 . 0)
(43 . 0.0) (10 4754.9023755656 3865.0071266968) (10 4772.5511312217 3883.8616515837) (10 4777.5268099548
3914.0271493213))
((0 . "LWPOLYLINE") (100 . "AcDbEntity") (8 . "PLANTS") (62 . 94) (370 . 13) (100 . "AcDbPolyline") (90 . 2) (70 . 0)
(43 . 0.0) (10 4754.9023755656 3857.4660633484) (10 4785.0678733032 3846.1538461538))
((0 . "LWPOLYLINE") (100 . "AcDbEntity") (8 . "PLANTS") (62 . 94) (370 . 13) (100 . "AcDbPolyline") (90 . 2) (70 . 0)
(43 . 0.0) (10 4758.6722850679 3932.8804298643) (10 4777.5268099548 3914.0271493213))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4758.6722850679 3932.8804298643 0.0) (10 4772.1456409152 3976.6563719926 0.0) (10 4759.6571013535
4023.6425995463 0.0) (10 4762.39244937 4068.7278572232 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4826.5455882353 426.0944570136 0.0) (10 4803.9037242744 400.7717207614 0.0) (10 4758.6295825356
376.6200943302 0.0) (10 4758.6722850679 335.596719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4852.9411764706 358.2211538462 0.0) (10 4814.5285660026 376.6829296331 0.0) (10 4795.2485470328
325.5072233108 0.0) (10 4758.6722850679 335.596719457 0.0))
((0 . "LWPOLYLINE") (100 . "AcDbEntity") (8 . "PLANTS") (62 . 94) (370 . 13) (100 . "AcDbPolyline") (90 . 2) (70 . 0)
(43 . 0.0) (10 4773.7556561086 961.5384615385) (10 4762.443438914 1003.0175339367))
((0 . "LWPOLYLINE") (100 . "AcDbEntity") (8 . "PLANTS") (62 . 94) (370 . 13) (100 . "AcDbPolyline") (90 . 2) (70 . 0)
(43 . 0.0) (10 4769.9845022624 1014.3297511312) (10 4762.443438914 1003.0175339367))
((0 . "LWPOLYLINE") (100 . "AcDbEntity") (8 . "PLANTS") (62 . 94) (370 . 13) (100 . "AcDbPolyline") (90 . 2) (70 . 0)
(43 . 0.0) (10 4766.2145927602 1044.4937782805) (10 4766.2145927602 1055.8059954751))
((0 . "LWPOLYLINE") (100 . "AcDbEntity") (8 . "PLANTS") (62 . 94) (370 . 13) (100 . "AcDbPolyline") (90 . 2) (70 . 0)
(43 . 0.0) (10 4767.3660401505 1158.2953500124) (10 4766.2145927602 1055.8059954751))
((0 . "LWPOLYLINE") (100 . "AcDbEntity") (8 . "PLANTS") (62 . 94) (370 . 13) (100 . "AcDbPolyline") (90 . 2) (70 . 0)
(43 . 0.0) (10 4785.0678733032 1063.3484162896) (10 4766.2145927602 1055.8059954751))
((0 . "LWPOLYLINE") (100 . "AcDbEntity") (8 . "PLANTS") (62 . 94) (370 . 13) (100 . "AcDbPolyline") (90 . 3) (70 . 0)
(43 . 0.0) (10 4766.2145927602 1044.4937782805) (10 4769.8366515837 1036.9466063348) (10 4769.9845022624
1014.3297511312))
((0 . "LWPOLYLINE") (100 . "AcDbEntity") (8 . "PLANTS") (62 . 94) (370 . 13) (100 . "AcDbPolyline") (90 . 3) (70 . 0)
(43 . 0.0) (10 4769.9845022624 1014.3297511312) (10 4803.9211538462 1013.2726244344) (10 4837.8578054299
984.1628959276))
((0 . "LWPOLYLINE") (100 . "AcDbEntity") (8 . "PLANTS") (62 . 94) (370 . 13) (100 . "AcDbPolyline") (90 . 2) (70 . 0)
(43 . 0.0) (10 4773.7556561086 961.5384615385) (10 4796.3800904977 957.7686651584))
((0 . "LWPOLYLINE") (100 . "AcDbEntity") (8 . "PLANTS") (62 . 94) (370 . 13) (100 . "AcDbPolyline") (90 . 2) (70 . 0)
(43 . 0.0) (10 4777.5268099548 3914.0271493213) (10 4807.6923076923 3925.3393665158))
((0 . "LWPOLYLINE") (100 . "AcDbEntity") (8 . "PLANTS") (62 . 94) (370 . 13) (100 . "AcDbPolyline") (90 . 3) (70 . 0)
(43 . 0.0) (10 4798.5497725136 3733.0316742081) (10 4799.9962669683 3748.1150452489) (10 4777.5268099548
3785.8216063348))
((0 . "LWPOLYLINE") (100 . "AcDbEntity") (8 . "PLANTS") (62 . 94) (370 . 13) (100 . "AcDbPolyline") (90 . 3) (70 . 0)
(43 . 0.0) (10 4834.0878959276 3808.446040724) (10 4792.6089366516 3796.0783936652) (10 4777.5268099548
3785.8216063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4856.7123303168 245.0989819004 0.0) (10 4839.1930411072 225.5217117452 0.0) (10 4802.8309020968
223.6245134227 0.0) (10 4781.296719457 237.5565610859 0.0))
((0 . "LWPOLYLINE") (100 . "AcDbEntity") (8 . "PLANTS") (62 . 94) (370 . 13) (100 . "AcDbPolyline") (90 . 3) (70 . 0)
(43 . 0.0) (10 4811.4634615385 279.0356334842) (10 4788.9929864253 260.1809954751) (10 4781.296719457 237.556561086))
((0 . "LWPOLYLINE") (100 . "AcDbEntity") (8 . "PLANTS") (62 . 94) (370 . 13) (100 . "AcDbPolyline") (90 . 3) (70 . 0)
(43 . 0.0) (10 4849.1700226244 904.9773755656) (10 4803.9211538462 905.1251131222) (10 4788.8390271493 908.7471719457))
((0 . "LWPOLYLINE") (100 . "AcDbEntity") (8 . "PLANTS") (62 . 94) (370 . 13) (100 . "AcDbPolyline") (90 . 3) (70 . 0)
(43 . 0.0) (10 4796.3800904977 957.7686651584) (10 4796.2320135747 935.1442307692) (10 4788.8390271493 908.7471719457))
((0 . "LWPOLYLINE") (100 . "AcDbEntity") (8 . "PLANTS") (62 . 94) (370 . 13) (100 . "AcDbPolyline") (90 . 2) (70 . 0)
(43 . 0.0) (10 4792.6089366516 463.8009049774) (10 4803.9211538462 467.5707013575))
((0 . "LWPOLYLINE") (100 . "AcDbEntity") (8 . "PLANTS") (62 . 94) (370 . 13) (100 . "AcDbPolyline") (90 . 3) (70 . 0)
(43 . 0.0) (10 4792.6089366516 312.9722850679) (10 4796.5347285068 314.4946832579) (10 4811.4634615385 305.4298642534))
((0 . "LWPOLYLINE") (100 . "AcDbEntity") (8 . "PLANTS") (62 . 94) (370 . 13) (100 . "AcDbPolyline") (90 . 3) (70 . 0)
(43 . 0.0) (10 4796.3800904977 957.7686651584) (10 4811.4634615385 958.9720588235) (10 4837.8578054299 984.1628959276))
((0 . "LWPOLYLINE") (100 . "AcDbEntity") (8 . "PLANTS") (62 . 94) (370 . 13) (100 . "AcDbPolyline") (90 . 3) (70 . 0)
(43 . 0.0) (10 4800.1512443439 1070.8908371041) (10 4822.775678733 1089.5817873303) (10 4845.4001131222
1082.2030542986))
((0 . "LWPOLYLINE") (100 . "AcDbEntity") (8 . "PLANTS") (62 . 94) (370 . 13) (100 . "AcDbPolyline") (90 . 3) (70 . 0)
(43 . 0.0) (10 4826.5455882353 452.4886877828) (10 4815.3817873303 453.6935520362) (10 4803.9211538462 467.5707013575))
((0 . "LWPOLYLINE") (100 . "AcDbEntity") (8 . "PLANTS") (62 . 94) (370 . 13) (100 . "AcDbPolyline") (90 . 2) (70 . 0)
(43 . 0.0) (10 4803.9211538462 467.5707013575) (10 4830.3167420814 493.967760181))
((0 . "LWPOLYLINE") (100 . "AcDbEntity") (8 . "PLANTS") (62 . 94) (370 . 13) (100 . "AcDbPolyline") (90 . 3) (70 . 0)
(43 . 0.0) (10 4807.6923076923 4000.7537330317) (10 4803.9211538462 3978.1292986425) (10 4807.6923076923
3925.3393665158))
((0 . "LWPOLYLINE") (100 . "AcDbEntity") (8 . "PLANTS") (62 . 94) (370 . 13) (100 . "AcDbPolyline") (90 . 3) (70 . 0)
(43 . 0.0) (10 4807.6923076923 4000.7537330317) (10 4811.4634615385 4068.6270361991) (10 4811.4633774272
4078.8306953527))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.1986768596)
(40 . 0.3607066439) (40 . 1) (40 . 1) (40 . 1) (40 . 1) (10 4856.7123303167 4046.0026018099 0.0) (10 4865.6298606428
4055.3531781583 0.0) (10 4886.1678599417 4056.0897639998 0.0) (10 4889.6381844862 4008.2079193917 0.0) (10 4828.36440762
3991.5529030471 0.0) (10 4807.6923076923 4000.7537330317 0.0))
((0 . "LWPOLYLINE") (100 . "AcDbEntity") (8 . "PLANTS") (62 . 94) (370 . 13) (100 . "AcDbPolyline") (90 . 3) (70 . 0)
(43 . 0.0) (10 4807.6923076923 3925.3393665158) (10 4825.3483031674 3902.7149321267) (10 4826.5455882353
3887.631561086))
((0 . "LWPOLYLINE") (100 . "AcDbEntity") (8 . "PLANTS") (62 . 94) (370 . 13) (100 . "AcDbPolyline") (90 . 2) (70 . 0)
(43 . 0.0) (10 4807.6923076923 3880.0904977376) (10 4826.5455882353 3887.631561086))
((0 . "LWPOLYLINE") (100 . "AcDbEntity") (8 . "PLANTS") (62 . 94) (370 . 13) (100 . "AcDbPolyline") (90 . 2) (70 . 0)
(43 . 0.0) (10 4811.4634615385 279.0356334842) (10 4811.4634615385 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4852.9411764706 328.0542986425 0.0) (10 4831.6038343686 330.6504465662 0.0) (10 4832.1148665189
302.6622039438 0.0) (10 4811.4634615385 305.4298642534 0.0))
((0 . "LWPOLYLINE") (100 . "AcDbEntity") (8 . "PLANTS") (62 . 94) (370 . 13) (100 . "AcDbPolyline") (90 . 2) (70 . 0)
(43 . 0.0) (10 4811.4634615385 279.0356334842) (10 4849.1700226244 275.2630090498))
((0 . "LWPOLYLINE") (100 . "AcDbEntity") (8 . "PLANTS") (62 . 94) (370 . 13) (100 . "AcDbPolyline") (90 . 2) (70 . 0)
(43 . 0.0) (10 4898.1900452489 3887.631561086) (10 4826.5455882353 3887.631561086))
((0 . "LWPOLYLINE") (100 . "AcDbEntity") (8 . "PLANTS") (62 . 94) (370 . 13) (100 . "AcDbPolyline") (90 . 2) (70 . 0)
(43 . 0.0) (10 4826.5455882353 452.4886877828) (10 4826.5455882353 426.0944570136))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4826.5455882353 452.4886877828 0.0) (10 4845.455731504 457.3488590747 0.0) (10 4853.6824489643
488.4293344153 0.0) (10 4830.3167420814 493.967760181 0.0))
((0 . "LWPOLYLINE") (100 . "AcDbEntity") (8 . "PLANTS") (62 . 94) (370 . 13) (100 . "AcDbPolyline") (90 . 3) (70 . 0)
(43 . 0.0) (10 4826.5455882353 426.0944570136) (10 4837.8584841629 422.1685520362) (10 4856.7123303167 403.4700226244))
((0 . "LWPOLYLINE") (100 . "AcDbEntity") (8 . "PLANTS") (62 . 94) (370 . 13) (100 . "AcDbPolyline") (90 . 2) (70 . 0)
(43 . 0.0) (10 4830.3167420814 509.0497737557) (10 4830.3167420814 493.967760181))
((0 . "LWPOLYLINE") (100 . "AcDbEntity") (8 . "PLANTS") (62 . 94) (370 . 13) (100 . "AcDbPolyline") (90 . 3) (70 . 0)
(43 . 0.0) (10 4845.4001131222 3978.1292986425) (10 4841.628959276 3970.5882352941) (10 4834.0878959276 3966.817081448))
((0 . "LWPOLYLINE") (100 . "AcDbEntity") (8 . "PLANTS") (62 . 94) (370 . 13) (100 . "AcDbPolyline") (90 . 3) (70 . 0)
(43 . 0.0) (10 4913.2734162896 3819.7582579186) (10 4852.9411764706 3804.8239819005) (10 4834.0878959276
3808.446040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4834.0878959276 3808.446040724 0.0) (10 4830.3488553167 3831.6665630644 0.0) (10 4853.8590366724
3852.038410316 0.0) (10 4875.5656108597 3853.6949095023 0.0))
((0 . "LWPOLYLINE") (100 . "AcDbEntity") (8 . "PLANTS") (62 . 94) (370 . 13) (100 . "AcDbPolyline") (90 . 2) (70 . 0)
(43 . 0.0) (10 4852.9411764706 984.1628959276) (10 4837.8578054299 984.1628959276))
((0 . "LWPOLYLINE") (100 . "AcDbEntity") (8 . "PLANTS") (62 . 94) (370 . 13) (100 . "AcDbPolyline") (90 . 3) (70 . 0)
(43 . 0.0) (10 4901.961199095 3665.1583710407) (10 4886.7297511312 3643.5906108597) (10 4880.3880374052
3641.0838248578))
((0 . "LWPOLYLINE") (100 . "AcDbEntity") (8 . "PLANTS") (62 . 94) (370 . 13) (100 . "AcDbPolyline") (90 . 2) (70 . 0)
(43 . 0.0) (10 4845.4001131222 1036.9541855204) (10 4856.7123303167 1040.7239819005))
((0 . "LWPOLYLINE") (100 . "AcDbEntity") (8 . "PLANTS") (62 . 94) (370 . 13) (100 . "AcDbPolyline") (90 . 2) (70 . 0)
(43 . 0.0) (10 4849.1700226244 904.9773755656) (10 4856.7123303167 931.3716063348))
((0 . "LWPOLYLINE") (100 . "AcDbEntity") (8 . "PLANTS") (62 . 94) (370 . 13) (100 . "AcDbPolyline") (90 . 3) (70 . 0)
(43 . 0.0) (10 4894.4188914027 908.7471719457) (10 4883.1066742081 905.1251131222) (10 4849.1700226244 904.9773755656))
((0 . "LWPOLYLINE") (100 . "AcDbEntity") (8 . "PLANTS") (62 . 94) (370 . 13) (100 . "AcDbPolyline") (90 . 3) (70 . 0)
(43 . 0.0) (10 4856.7123303167 245.0989819005) (10 4850.2266968326 256.411199095) (10 4849.1700226244 275.2630090498))
((0 . "LWPOLYLINE") (100 . "AcDbEntity") (8 . "PLANTS") (62 . 94) (370 . 13) (100 . "AcDbPolyline") (90 . 3) (70 . 0)
(43 . 0.0) (10 4864.2533936652 294.1176470588) (10 4856.853280543 290.1925339367) (10 4849.1700226244 275.2630090498))
((0 . "LWPOLYLINE") (100 . "AcDbEntity") (8 . "PLANTS") (62 . 94) (370 . 13) (100 . "AcDbPolyline") (90 . 3) (70 . 0)
(43 . 0.0) (10 4901.961199095 976.6204751131) (10 4864.2533936652 976.7757918552) (10 4852.9411764706 984.1628959276))
((0 . "LWPOLYLINE") (100 . "AcDbEntity") (8 . "PLANTS") (62 . 94) (370 . 13) (100 . "AcDbPolyline") (90 . 3) (70 . 0)
(43 . 0.0) (10 4856.7123303167 1040.7239819005) (10 4860.328280543 999.2449095023) (10 4852.9411764706 984.1628959276))
((0 . "LWPOLYLINE") (100 . "AcDbEntity") (8 . "PLANTS") (62 . 94) (370 . 13) (100 . "AcDbPolyline") (90 . 2) (70 . 0)
(43 . 0.0) (10 4852.9411764706 358.2211538462) (10 4852.9411764706 328.0542986425))
((0 . "LWPOLYLINE") (100 . "AcDbEntity") (8 . "PLANTS") (62 . 94) (370 . 13) (100 . "AcDbPolyline") (90 . 2) (70 . 0)
(43 . 0.0) (10 4860.482239819 361.9909502262) (10 4852.9411764706 358.2211538462))
((0 . "LWPOLYLINE") (100 . "AcDbEntity") (8 . "PLANTS") (62 . 94) (370 . 13) (100 . "AcDbPolyline") (90 . 3) (70 . 0)
(43 . 0.0) (10 4864.2533936652 294.1176470588) (10 4863.0492081448 316.742081448) (10 4852.9411764706 328.0542986425))
((0 . "LWPOLYLINE") (100 . "AcDbEntity") (8 . "PLANTS") (62 . 94) (370 . 13) (100 . "AcDbPolyline") (90 . 2) (70 . 0)
(43 . 0.0) (10 4856.7123303167 3925.3393665158) (10 4860.482239819 3936.6515837104))
((0 . "LWPOLYLINE") (100 . "AcDbEntity") (8 . "PLANTS") (62 . 94) (370 . 13) (100 . "AcDbPolyline") (90 . 2) (70 . 0)
(43 . 0.0) (10 4879.3367647059 3714.1783936652) (10 4873.7594914925 3716.0373824863))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4913.2734162896 3778.2805429864 0.0) (10 4891.3720818422 3775.0531897226 0.0) (10 4859.1707837028
3758.7988272525 0.0) (10 4858.437571892 3733.0316742081 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4856.7123303167 1040.7239819005 0.0) (10 4855.7445143329 1063.1614912786 0.0) (10 4898.0837026376
1051.4445840746 0.0) (10 4879.3367647059 1082.2030542986 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4935.8978506787 367.6470588235 0.0) (10 4904.9639598102 371.1273224869 0.0) (10 4890.5335840571
408.8602825333 0.0) (10 4856.7123303167 403.4700226244 0.0))
((0 . "LWPOLYLINE") (100 . "AcDbEntity") (8 . "PLANTS") (62 . 94) (370 . 13) (100 . "AcDbPolyline") (90 . 2) (70 . 0)
(43 . 0.0) (10 4856.7123303167 403.4700226244) (10 4860.482239819 361.9909502262))
((0 . "LWPOLYLINE") (100 . "AcDbEntity") (8 . "PLANTS") (62 . 94) (370 . 13) (100 . "AcDbPolyline") (90 . 3) (70 . 0)
(43 . 0.0) (10 4856.7123303167 245.0989819005) (10 4890.6483031674 245.2522624434) (10 4901.961199095 252.6385746606))
((0 . "LWPOLYLINE") (100 . "AcDbEntity") (8 . "PLANTS") (62 . 94) (370 . 13) (100 . "AcDbPolyline") (90 . 3) (70 . 0)
(43 . 0.0) (10 4879.3367647059 1082.2030542986) (10 4861.6869909502 1097.2850678733) (10 4860.482239819
1116.1397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4860.482239819 361.9909502262 0.0) (10 4882.7223826225 359.5209175004 0.0) (10 4908.3182776802
340.5986786778 0.0) (10 4909.5022624434 316.742081448 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4969.8345022624 3917.7983031674 0.0) (10 4953.4594634695 3951.4887118698 0.0) (10 4893.6404391299
4004.7511001135 0.0) (10 4864.2533936651 3951.7349547511 0.0))
((0 . "LWPOLYLINE") (100 . "AcDbEntity") (8 . "PLANTS") (62 . 94) (370 . 13) (100 . "AcDbPolyline") (90 . 3) (70 . 0)
(43 . 0.0) (10 4864.2533936652 294.1176470588) (10 4879.3367647059 289.1492081448) (10 4894.4188914027 275.2630090498))
((0 . "LWPOLYLINE") (100 . "AcDbEntity") (8 . "PLANTS") (62 . 94) (370 . 13) (100 . "AcDbPolyline") (90 . 2) (70 . 0)
(43 . 0.0) (10 4886.8778280543 3921.5682126697) (10 4875.5656108597 3921.5682126697))
((0 . "LWPOLYLINE") (100 . "AcDbEntity") (8 . "PLANTS") (62 . 94) (370 . 13) (100 . "AcDbPolyline") (90 . 2) (70 . 0)
(43 . 0.0) (10 4898.1900452489 1101.0548642534) (10 4879.3367647059 1082.2030542986))
((0 . "LWPOLYLINE") (100 . "AcDbEntity") (8 . "PLANTS") (62 . 94) (370 . 13) (100 . "AcDbPolyline") (90 . 3) (70 . 0)
(43 . 0.0) (10 4898.1900452489 3887.631561086) (10 4896.9924208145 3902.7149321267) (10 4886.8778280543
3921.5682126697))
((0 . "LWPOLYLINE") (100 . "AcDbEntity") (8 . "PLANTS") (62 . 94) (370 . 13) (100 . "AcDbPolyline") (90 . 2) (70 . 0)
(43 . 0.0) (10 4890.6489819005 3929.110520362) (10 4886.8778280543 3921.5682126697))
((0 . "LWPOLYLINE") (100 . "AcDbEntity") (8 . "PLANTS") (62 . 94) (370 . 13) (100 . "AcDbPolyline") (90 . 2) (70 . 0)
(43 . 0.0) (10 4894.4188914027 908.7471719457) (10 4890.6489819005 923.8320135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5041.4777149321 916.2895927602 0.0) (10 4992.8846019402 911.1282166782 0.0) (10 4942.9630714802
885.2797503791 0.0) (10 4894.4188914027 908.7471719457 0.0))
((0 . "LWPOLYLINE") (100 . "AcDbEntity") (8 . "PLANTS") (62 . 94) (370 . 13) (100 . "AcDbPolyline") (90 . 2) (70 . 0)
(43 . 0.0) (10 4901.961199095 252.6385746606) (10 4894.4188914027 275.2630090498))
((0 . "LWPOLYLINE") (100 . "AcDbEntity") (8 . "PLANTS") (62 . 94) (370 . 13) (100 . "AcDbPolyline") (90 . 2) (70 . 0)
(43 . 0.0) (10 4894.4188914027 275.2630090498) (10 4909.5022624434 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4969.8345022624 3917.7983031674 0.0) (10 4952.5010965476 3897.6677724384 0.0) (10 4925.3935946903
3882.5449418133 0.0) (10 4898.1900452489 3887.631561086 0.0))
((0 . "LWPOLYLINE") (100 . "AcDbEntity") (8 . "PLANTS") (62 . 94) (370 . 13) (100 . "AcDbPolyline") (90 . 3) (70 . 0)
(43 . 0.0) (10 4909.5022624434 3714.1783936652) (10 4902.1090497738 3691.553959276) (10 4901.961199095 3665.1583710407))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4901.961199095 3665.1583710407 0.0) (10 4926.4229424913 3652.7205708287 0.0) (10 4942.7230297622
3678.9358210536 0.0) (10 4935.8978506787 3699.0950226244 0.0))
((0 . "LWPOLYLINE") (100 . "AcDbEntity") (8 . "PLANTS") (62 . 94) (370 . 13) (100 . "AcDbPolyline") (90 . 3) (70 . 0)
(43 . 0.0) (10 4901.961199095 976.6204751131) (10 4920.814479638 972.9990950226) (10 4943.4389140271 984.1628959276))
((0 . "LWPOLYLINE") (100 . "AcDbEntity") (8 . "PLANTS") (62 . 94) (370 . 13) (100 . "AcDbPolyline") (90 . 3) (70 . 0)
(43 . 0.0) (10 4901.961199095 976.6204751131) (10 4903.1650452489 999.2400452489) (10 4920.814479638 1010.5571266968))
((0 . "LWPOLYLINE") (100 . "AcDbEntity") (8 . "PLANTS") (62 . 94) (370 . 13) (100 . "AcDbPolyline") (90 . 2) (70 . 0)
(43 . 0.0) (10 4901.961199095 516.5921945701) (10 4939.667760181 516.5921945701))
((0 . "LWPOLYLINE") (100 . "AcDbEntity") (8 . "PLANTS") (62 . 94) (370 . 13) (100 . "AcDbPolyline") (90 . 2) (70 . 0)
(43 . 0.0) (10 4901.961199095 252.6385746606) (10 4909.5022624434 252.6385746606))
((0 . "LWPOLYLINE") (100 . "AcDbEntity") (8 . "PLANTS") (62 . 94) (370 . 13) (100 . "AcDbPolyline") (90 . 2) (70 . 0)
(43 . 0.0) (10 4909.5022624434 3714.1783936652) (10 4928.3555429864 3714.1783936652))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4909.5022624434 3714.1783936652 0.0) (10 4896.8731482406 3723.5651330279 0.0) (10 4895.0194427378
3748.9303098894 0.0) (10 4917.0433257919 3751.8849547511 0.0))
((0 . "LWPOLYLINE") (100 . "AcDbEntity") (8 . "PLANTS") (62 . 94) (370 . 13) (100 . "AcDbPolyline") (90 . 3) (70 . 0)
(43 . 0.0) (10 4950.9799773756 286.5752262443) (10 4924.5856334842 311.915158371) (10 4909.5022624434 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4984.9166289593 241.3263574661 0.0) (10 4962.6157346315 224.2261480323 0.0) (10 4924.0560708631
225.8801711231 0.0) (10 4909.5022624434 252.6385746606 0.0))
((0 . "LWPOLYLINE") (100 . "AcDbEntity") (8 . "PLANTS") (62 . 94) (370 . 13) (100 . "AcDbPolyline") (90 . 2) (70 . 0)
(43 . 0.0) (10 4950.9799773756 286.5752262443) (10 4909.5022624434 252.6385746606))
((0 . "LWPOLYLINE") (100 . "AcDbEntity") (8 . "PLANTS") (62 . 94) (370 . 13) (100 . "AcDbPolyline") (90 . 2) (70 . 0)
(43 . 0.0) (10 4913.2734162896 3819.7582579186) (10 4913.2734162896 3849.925))
((0 . "LWPOLYLINE") (100 . "AcDbEntity") (8 . "PLANTS") (62 . 94) (370 . 13) (100 . "AcDbPolyline") (90 . 2) (70 . 0)
(43 . 0.0) (10 4932.1266968326 3812.2171945701) (10 4913.2734162896 3819.7582579186))
((0 . "LWPOLYLINE") (100 . "AcDbEntity") (8 . "PLANTS") (62 . 94) (370 . 13) (100 . "AcDbPolyline") (90 . 2) (70 . 0)
(43 . 0.0) (10 4913.2734162896 3778.2805429864) (10 4917.0433257919 3751.8849547511))
((0 . "LWPOLYLINE") (100 . "AcDbEntity") (8 . "PLANTS") (62 . 94) (370 . 13) (100 . "AcDbPolyline") (90 . 3) (70 . 0)
(43 . 0.0) (10 4913.2734162896 3778.2805429864) (10 4920.9625565611 3793.3570135747) (10 4932.1266968326
3800.9049773756))
((0 . "LWPOLYLINE") (100 . "AcDbEntity") (8 . "PLANTS") (62 . 94) (370 . 13) (100 . "AcDbPolyline") (90 . 2) (70 . 0)
(43 . 0.0) (10 4917.0433257919 3751.8849547511) (10 4932.1266968326 3751.8849547511))
((0 . "LWPOLYLINE") (100 . "AcDbEntity") (8 . "PLANTS") (62 . 94) (370 . 13) (100 . "AcDbPolyline") (90 . 3) (70 . 0)
(43 . 0.0) (10 4920.814479638 1010.5571266968) (10 4931.0707013575 1002.8691176471) (10 4943.4389140271 984.1628959276))
((0 . "LWPOLYLINE") (100 . "AcDbEntity") (8 . "PLANTS") (62 . 94) (370 . 13) (100 . "AcDbPolyline") (90 . 2) (70 . 0)
(43 . 0.0) (10 4928.3555429864 1040.7239819005) (10 4920.814479638 1010.5571266968))
((0 . "LWPOLYLINE") (100 . "AcDbEntity") (8 . "PLANTS") (62 . 94) (370 . 13) (100 . "AcDbPolyline") (90 . 2) (70 . 0)
(43 . 0.0) (10 4935.8978506787 3699.0950226244) (10 4928.3555429864 3714.1783936652))
((0 . "LWPOLYLINE") (100 . "AcDbEntity") (8 . "PLANTS") (62 . 94) (370 . 13) (100 . "AcDbPolyline") (90 . 2) (70 . 0)
(43 . 0.0) (10 4928.3555429864 3714.1783936652) (10 4932.1266968326 3751.8849547511))
((0 . "LWPOLYLINE") (100 . "AcDbEntity") (8 . "PLANTS") (62 . 94) (370 . 13) (100 . "AcDbPolyline") (90 . 2) (70 . 0)
(43 . 0.0) (10 4928.3555429864 1040.7239819005) (10 4928.3555429864 1052.036199095))
((0 . "LWPOLYLINE") (100 . "AcDbEntity") (8 . "PLANTS") (62 . 94) (370 . 13) (100 . "AcDbPolyline") (90 . 2) (70 . 0)
(43 . 0.0) (10 4928.3555429864 1040.7239819005) (10 4962.2921945701 1029.4117647059))
((0 . "LWPOLYLINE") (100 . "AcDbEntity") (8 . "PLANTS") (62 . 94) (370 . 13) (100 . "AcDbPolyline") (90 . 2) (70 . 0)
(43 . 0.0) (10 4932.1266968326 3812.2171945701) (10 4932.1266968326 3800.9049773756))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4932.1266968326 3812.2171945701 0.0) (10 4956.2614881093 3815.6518844956 0.0) (10 4964.1452904032
3845.0614231236 0.0) (10 4988.6877828054 3846.1538461538 0.0))
((0 . "LWPOLYLINE") (100 . "AcDbEntity") (8 . "PLANTS") (62 . 94) (370 . 13) (100 . "AcDbPolyline") (90 . 3) (70 . 0)
(43 . 0.0) (10 4947.2100678733 3755.6561085973) (10 4946.0053167421 3785.8216063348) (10 4932.1266968326
3800.9049773756))
((0 . "LWPOLYLINE") (100 . "AcDbEntity") (8 . "PLANTS") (62 . 94) (370 . 13) (100 . "AcDbPolyline") (90 . 3) (70 . 0)
(43 . 0.0) (10 4947.2100678733 3755.6561085973) (10 4935.8978506787 3755.6561085973) (10 4932.1266968326
3751.8849547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4932.1266968326 3589.7433257919 0.0) (10 4934.0871573305 3613.549059395 0.0) (10 4955.3981637083
3647.3952859062 0.0) (10 4984.9166289593 3627.4505656109 0.0))
((0 . "LWPOLYLINE") (100 . "AcDbEntity") (8 . "PLANTS") (62 . 94) (370 . 13) (100 . "AcDbPolyline") (90 . 2) (70 . 0)
(43 . 0.0) (10 4935.8978506787 3699.0950226244) (10 4950.9799773756 3699.0950226244))
((0 . "LWPOLYLINE") (100 . "AcDbEntity") (8 . "PLANTS") (62 . 94) (370 . 13) (100 . "AcDbPolyline") (90 . 2) (70 . 0)
(43 . 0.0) (10 4954.7511312217 935.1442307692) (10 4935.8978506787 938.9140271493))
((0 . "LWPOLYLINE") (100 . "AcDbEntity") (8 . "PLANTS") (62 . 94) (370 . 13) (100 . "AcDbPolyline") (90 . 2) (70 . 0)
(43 . 0.0) (10 4935.8978506787 367.6470588235) (10 4943.4389140271 365.7607466063))
((0 . "LWPOLYLINE") (100 . "AcDbEntity") (8 . "PLANTS") (62 . 94) (370 . 13) (100 . "AcDbPolyline") (90 . 3) (70 . 0)
(43 . 0.0) (10 4935.8978506787 367.6470588235) (10 4935.8978506787 361.9909502262) (10 4943.4389140271 358.2211538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4935.8978506787 367.6470588235 0.0) (10 4921.0109413856 395.1813955019 0.0) (10 4948.3554668428
428.2053968287 0.0) (10 4977.3755656109 414.782239819 0.0))
((0 . "LWPOLYLINE") (100 . "AcDbEntity") (8 . "PLANTS") (62 . 94) (370 . 13) (100 . "AcDbPolyline") (90 . 2) (70 . 0)
(43 . 0.0) (10 4939.667760181 3457.7679864253) (10 4950.9799773756 3495.4751131222))
((0 . "LWPOLYLINE") (100 . "AcDbEntity") (8 . "PLANTS") (62 . 94) (370 . 13) (100 . "AcDbPolyline") (90 . 2) (70 . 0)
(43 . 0.0) (10 4954.7511312217 3386.1234162896) (10 4943.4389140271 3371.0407239819))
((0 . "LWPOLYLINE") (100 . "AcDbEntity") (8 . "PLANTS") (62 . 94) (370 . 13) (100 . "AcDbPolyline") (90 . 3) (70 . 0)
(43 . 0.0) (10 4943.4389140271 984.1628959276) (10 4958.5153846154 987.0385746606) (10 4966.0633484163 995.4751131222))
((0 . "LWPOLYLINE") (100 . "AcDbEntity") (8 . "PLANTS") (62 . 94) (370 . 13) (100 . "AcDbPolyline") (90 . 2) (70 . 0)
(43 . 0.0) (10 4943.4389140271 358.2211538462) (10 4943.4389140271 365.7607466063))
((0 . "LWPOLYLINE") (100 . "AcDbEntity") (8 . "PLANTS") (62 . 94) (370 . 13) (100 . "AcDbPolyline") (90 . 3) (70 . 0)
(43 . 0.0) (10 4966.0633484163 373.3031674208) (10 4947.3640271493 372.1052036199) (10 4943.4389140271 365.7607466063))
((0 . "LWPOLYLINE") (100 . "AcDbEntity") (8 . "PLANTS") (62 . 94) (370 . 13) (100 . "AcDbPolyline") (90 . 3) (70 . 0)
(43 . 0.0) (10 4943.4389140271 358.2211538462) (10 4950.9868778281 344.3411764706) (10 4969.8345022624 339.3665158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4947.2100678733 3755.6561085973 0.0) (10 4988.5625126194 3748.6240057218 0.0) (10 4953.0038951629
3695.3359795935 0.0) (10 4984.9166289593 3676.4705882353 0.0))
((0 . "LWPOLYLINE") (100 . "AcDbEntity") (8 . "PLANTS") (62 . 94) (370 . 13) (100 . "AcDbPolyline") (90 . 2) (70 . 0)
(43 . 0.0) (10 4950.9799773756 286.5752262443) (10 4958.5222850679 286.5752262443))
((0 . "LWPOLYLINE") (100 . "AcDbEntity") (8 . "PLANTS") (62 . 94) (370 . 13) (100 . "AcDbPolyline") (90 . 3) (70 . 0)
(43 . 0.0) (10 4958.5222850679 1138.1675994284) (10 4958.5222850679 1127.4519230769) (10 4962.2921945701
1123.6792986425))
((0 . "LWPOLYLINE") (100 . "AcDbEntity") (8 . "PLANTS") (62 . 94) (370 . 13) (100 . "AcDbPolyline") (90 . 2) (70 . 0)
(43 . 0.0) (10 4981.146719457 282.8054298643) (10 4958.5222850679 286.5752262443))
((0 . "LWPOLYLINE") (100 . "AcDbEntity") (8 . "PLANTS") (62 . 94) (370 . 13) (100 . "AcDbPolyline") (90 . 3) (70 . 0)
(43 . 0.0) (10 4969.8345022624 339.3665158371) (10 4965.9087104072 301.6600678733) (10 4958.5222850679 286.5752262443))
((0 . "LWPOLYLINE") (100 . "AcDbEntity") (8 . "PLANTS") (62 . 94) (370 . 13) (100 . "AcDbPolyline") (90 . 2) (70 . 0)
(43 . 0.0) (10 4962.2921945701 1029.4117647059) (10 4966.0633484163 995.4751131222))
((0 . "LWPOLYLINE") (100 . "AcDbEntity") (8 . "PLANTS") (62 . 94) (370 . 13) (100 . "AcDbPolyline") (90 . 2) (70 . 0)
(43 . 0.0) (10 4973.6044117647 1048.2664027149) (10 4962.2921945701 1029.4117647059))
((0 . "LWPOLYLINE") (100 . "AcDbEntity") (8 . "PLANTS") (62 . 94) (370 . 13) (100 . "AcDbPolyline") (90 . 3) (70 . 0)
(43 . 0.0) (10 5037.7078054299 1010.5571266968) (10 5015.0833710407 999.3933257919) (10 4966.0633484163 995.4751131222))
((0 . "LWPOLYLINE") (100 . "AcDbEntity") (8 . "PLANTS") (62 . 94) (370 . 13) (100 . "AcDbPolyline") (90 . 2) (70 . 0)
(43 . 0.0) (10 4981.146719457 365.7607466063) (10 4966.0633484163 373.3031674208))
((0 . "LWPOLYLINE") (100 . "AcDbEntity") (8 . "PLANTS") (62 . 94) (370 . 13) (100 . "AcDbPolyline") (90 . 3) (70 . 0)
(43 . 0.0) (10 4977.3755656109 395.92760181) (10 4971.0252262443 392.0024886878) (10 4966.0633484163 373.3031674208))
((0 . "LWPOLYLINE") (100 . "AcDbEntity") (8 . "PLANTS") (62 . 94) (370 . 13) (100 . "AcDbPolyline") (90 . 2) (70 . 0)
(43 . 0.0) (10 4969.8345022624 3917.7983031674) (10 5003.7711538462 3914.0271493213))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4969.8345022624 1093.5152714932 0.0) (10 4981.2781726933 1073.8211504786 0.0) (10 5000.2301065781
1046.5131929705 0.0) (10 5026.3955882353 1048.2664027149 0.0))
((0 . "LWPOLYLINE") (100 . "AcDbEntity") (8 . "PLANTS") (62 . 94) (370 . 13) (100 . "AcDbPolyline") (90 . 2) (70 . 0)
(43 . 0.0) (10 4981.146719457 365.7607466063) (10 4969.8345022624 339.3665158371))
((0 . "LWPOLYLINE") (100 . "AcDbEntity") (8 . "PLANTS") (62 . 94) (370 . 13) (100 . "AcDbPolyline") (90 . 2) (70 . 0)
(43 . 0.0) (10 4977.3755656109 395.92760181) (10 4977.3755656109 414.782239819))
((0 . "LWPOLYLINE") (100 . "AcDbEntity") (8 . "PLANTS") (62 . 94) (370 . 13) (100 . "AcDbPolyline") (90 . 2) (70 . 0)
(43 . 0.0) (10 4984.9166289593 478.882918552) (10 4977.3755656109 414.782239819))
((0 . "LWPOLYLINE") (100 . "AcDbEntity") (8 . "PLANTS") (62 . 94) (370 . 13) (100 . "AcDbPolyline") (90 . 2) (70 . 0)
(43 . 0.0) (10 4996.2288461538 392.1578054299) (10 4977.3755656109 395.92760181))
((0 . "LWPOLYLINE") (100 . "AcDbEntity") (8 . "PLANTS") (62 . 94) (370 . 13) (100 . "AcDbPolyline") (90 . 3) (70 . 0)
(43 . 0.0) (10 4996.2288461538 392.1578054299) (10 4995.025 377.0805429864) (10 4981.146719457 365.7607466063))
((0 . "LWPOLYLINE") (100 . "AcDbEntity") (8 . "PLANTS") (62 . 94) (370 . 13) (100 . "AcDbPolyline") (90 . 2) (70 . 0)
(43 . 0.0) (10 4984.9166289593 241.3263574661) (10 4981.146719457 282.8054298643))
((0 . "LWPOLYLINE") (100 . "AcDbEntity") (8 . "PLANTS") (62 . 94) (370 . 13) (100 . "AcDbPolyline") (90 . 3) (70 . 0)
(43 . 0.0) (10 4981.146719457 282.8054298643) (10 5003.9190045249 316.5936651584) (10 5018.853280543 324.2845022624))
((0 . "LWPOLYLINE") (100 . "AcDbEntity") (8 . "PLANTS") (62 . 94) (370 . 13) (100 . "AcDbPolyline") (90 . 2) (70 . 0)
(43 . 0.0) (10 4984.9166289593 3676.4705882353) (10 4984.9166289593 3627.4505656109))
((0 . "LWPOLYLINE") (100 . "AcDbEntity") (8 . "PLANTS") (62 . 94) (370 . 13) (100 . "AcDbPolyline") (90 . 2) (70 . 0)
(43 . 0.0) (10 4992.4589366516 3680.2417420814) (10 4984.9166289593 3676.4705882353))
((0 . "LWPOLYLINE") (100 . "AcDbEntity") (8 . "PLANTS") (62 . 94) (370 . 13) (100 . "AcDbPolyline") (90 . 2) (70 . 0)
(43 . 0.0) (10 4988.6877828054 3619.9095022624) (10 4984.9166289593 3627.4505656109))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4984.9166289593 241.3263574661 0.0) (10 5024.4294346679 222.9532868005 0.0) (10 5079.7336796239
216.9261653339 0.0) (10 5113.1221719457 248.8687782805 0.0))
((0 . "LWPOLYLINE") (100 . "AcDbEntity") (8 . "PLANTS") (62 . 94) (370 . 13) (100 . "AcDbPolyline") (90 . 2) (70 . 0)
(43 . 0.0) (10 5033.9366515837 3846.1538461538) (10 4988.6877828054 3846.1538461538))
((0 . "LWPOLYLINE") (100 . "AcDbEntity") (8 . "PLANTS") (62 . 94) (370 . 13) (100 . "AcDbPolyline") (90 . 3) (70 . 0)
(43 . 0.0) (10 4988.6877828054 3846.1538461538) (10 4992.6067873303 3883.8616515837) (10 5003.7711538462
3914.0271493213))
((0 . "LWPOLYLINE") (100 . "AcDbEntity") (8 . "PLANTS") (62 . 94) (370 . 13) (100 . "AcDbPolyline") (90 . 3) (70 . 0)
(43 . 0.0) (10 5037.7078054299 3616.1390271493) (10 5011.3122171946 3612.5162895928) (10 4988.6877828054
3619.9095022624))
((0 . "LWPOLYLINE") (100 . "AcDbEntity") (8 . "PLANTS") (62 . 94) (370 . 13) (100 . "AcDbPolyline") (90 . 2) (70 . 0)
(43 . 0.0) (10 4988.6877828054 3619.9095022624) (10 4992.4589366516 3589.7433257919))
((0 . "LWPOLYLINE") (100 . "AcDbEntity") (8 . "PLANTS") (62 . 94) (370 . 13) (100 . "AcDbPolyline") (90 . 3) (70 . 0)
(43 . 0.0) (10 4996.2288461538 3386.1234162896) (10 4985.2131221719 3427.5949095023) (10 4988.6877828054
3435.1435520362))
((0 . "LWPOLYLINE") (100 . "AcDbEntity") (8 . "PLANTS") (62 . 94) (370 . 13) (100 . "AcDbPolyline") (90 . 3) (70 . 0)
(43 . 0.0) (10 4992.4589366516 3789.592760181) (10 5022.6244343891 3788.5429864253) (10 5060.332239819 3766.9683257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4992.4589366516 3589.7433257919 0.0) (10 5027.2997970553 3597.0697442737 0.0) (10 5016.1264804922
3543.5693773787 0.0) (10 5049.0200226244 3544.4944570136 0.0))
((0 . "LWPOLYLINE") (100 . "AcDbEntity") (8 . "PLANTS") (62 . 94) (370 . 13) (100 . "AcDbPolyline") (90 . 3) (70 . 0)
(43 . 0.0) (10 4992.4589366516 3525.6412895928) (10 4988.6940045249 3567.1188914027) (10 4992.4589366516
3589.7433257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4992.4589366516 3525.6412895928 0.0) (10 5022.1268796649 3522.0427754396 0.0) (10 5013.2818873767
3483.8020544108 0.0) (10 5041.4777149321 3476.6211538462 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 4992.4589366516 3525.6412895928 0.0) (10 4979.0394443482 3515.1188776894 0.0) (10 4989.0709585144
3491.636260643 0.0) (10 4996.2288461538 3480.3924208145 0.0))
((0 . "LWPOLYLINE") (100 . "AcDbEntity") (8 . "PLANTS") (62 . 94) (370 . 13) (100 . "AcDbPolyline") (90 . 2) (70 . 0)
(43 . 0.0) (10 4992.4589366516 3318.2501131222) (10 4992.4589366516 3325.7918552036))
((0 . "LWPOLYLINE") (100 . "AcDbEntity") (8 . "PLANTS") (62 . 94) (370 . 13) (100 . "AcDbPolyline") (90 . 2) (70 . 0)
(43 . 0.0) (10 4996.2288461538 392.1578054299) (10 5015.0833710407 392.1578054299))
((0 . "LWPOLYLINE") (100 . "AcDbEntity") (8 . "PLANTS") (62 . 94) (370 . 13) (100 . "AcDbPolyline") (90 . 3) (70 . 0)
(43 . 0.0) (10 5011.3122171946 3921.5682126697) (10 5011.3122171946 3917.7983031674) (10 5003.7711538462
3914.0271493213))
((0 . "LWPOLYLINE") (100 . "AcDbEntity") (8 . "PLANTS") (62 . 94) (370 . 13) (100 . "AcDbPolyline") (90 . 2) (70 . 0)
(43 . 0.0) (10 5011.3122171946 3748.1150452489) (10 5003.7711538462 3748.1150452489))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.406575544) (40 .
1) (40 . 1) (40 . 1) (40 . 1) (10 5011.3122171946 3989.4415158371 0.0) (10 4987.0500297329 4004.529712868 0.0) (10
4963.6166226715 3990.3544393073 0.0) (10 4994.1743936467 3937.5206000685 0.0) (10 5011.3122171946 3936.6515837104 0.0))
((0 . "LWPOLYLINE") (100 . "AcDbEntity") (8 . "PLANTS") (62 . 94) (370 . 13) (100 . "AcDbPolyline") (90 . 2) (70 . 0)
(43 . 0.0) (10 5011.3122171946 3929.110520362) (10 5011.3122171946 3936.6515837104))
((0 . "LWPOLYLINE") (100 . "AcDbEntity") (8 . "PLANTS") (62 . 94) (370 . 13) (100 . "AcDbPolyline") (90 . 2) (70 . 0)
(43 . 0.0) (10 5011.3122171946 3936.6515837104) (10 5049.0200226244 3978.1292986425))
((0 . "LWPOLYLINE") (100 . "AcDbEntity") (8 . "PLANTS") (62 . 94) (370 . 13) (100 . "AcDbPolyline") (90 . 3) (70 . 0)
(43 . 0.0) (10 5011.3122171946 3929.110520362) (10 5015.0833710407 3929.110520362) (10 5018.853280543 3921.5682126697))
((0 . "LWPOLYLINE") (100 . "AcDbEntity") (8 . "PLANTS") (62 . 94) (370 . 13) (100 . "AcDbPolyline") (90 . 2) (70 . 0)
(43 . 0.0) (10 5011.3122171946 3929.110520362) (10 5011.3122171946 3921.5682126697))
((0 . "LWPOLYLINE") (100 . "AcDbEntity") (8 . "PLANTS") (62 . 94) (370 . 13) (100 . "AcDbPolyline") (90 . 2) (70 . 0)
(43 . 0.0) (10 5018.853280543 3921.5682126697) (10 5011.3122171946 3921.5682126697))
((0 . "LWPOLYLINE") (100 . "AcDbEntity") (8 . "PLANTS") (62 . 94) (370 . 13) (100 . "AcDbPolyline") (90 . 2) (70 . 0)
(43 . 0.0) (10 5015.0833710407 392.1578054299) (10 5015.0833710407 411.0096153846))
((0 . "LWPOLYLINE") (100 . "AcDbEntity") (8 . "PLANTS") (62 . 94) (370 . 13) (100 . "AcDbPolyline") (90 . 2) (70 . 0)
(43 . 0.0) (10 5015.0833710407 392.1578054299) (10 5030.1654977376 392.1578054299))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5015.0833710407 282.8054298642 0.0) (10 5037.0538346302 278.5322777968 0.0) (10 5041.5552783576
310.0670987225 0.0) (10 5037.7078054299 324.2845022624 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5088.6127828054 3904.5998868778 0.0) (10 5067.465534994 3919.3406321381 0.0) (10 5039.3574068942
3902.0171370458 0.0) (10 5018.853280543 3921.5682126697 0.0))
((0 . "LWPOLYLINE") (100 . "AcDbEntity") (8 . "PLANTS") (62 . 94) (370 . 13) (100 . "AcDbPolyline") (90 . 2) (70 . 0)
(43 . 0.0) (10 5018.853280543 3699.0950226244) (10 5037.7078054299 3695.3238687783))
((0 . "LWPOLYLINE") (100 . "AcDbEntity") (8 . "PLANTS") (62 . 94) (370 . 13) (100 . "AcDbPolyline") (90 . 3) (70 . 0)
(43 . 0.0) (10 5020.3181820355 1105.6434431297) (10 5026.2471719457 1078.4304298643) (10 5026.3955882353
1048.2664027149))
((0 . "LWPOLYLINE") (100 . "AcDbEntity") (8 . "PLANTS") (62 . 94) (370 . 13) (100 . "AcDbPolyline") (90 . 2) (70 . 0)
(43 . 0.0) (10 5018.853280543 324.2845022624) (10 5037.7078054299 324.2845022624))
((0 . "LWPOLYLINE") (100 . "AcDbEntity") (8 . "PLANTS") (62 . 94) (370 . 13) (100 . "AcDbPolyline") (90 . 3) (70 . 0)
(43 . 0.0) (10 5037.7078054299 369.5333710407) (10 5023.8220588235 350.6787330317) (10 5018.853280543 324.2845022624))
((0 . "LWPOLYLINE") (100 . "AcDbEntity") (8 . "PLANTS") (62 . 94) (370 . 13) (100 . "AcDbPolyline") (90 . 2) (70 . 0)
(43 . 0.0) (10 5037.7078054299 1040.7239819005) (10 5026.3955882353 1048.2664027149))
((0 . "LWPOLYLINE") (100 . "AcDbEntity") (8 . "PLANTS") (62 . 94) (370 . 13) (100 . "AcDbPolyline") (90 . 3) (70 . 0)
(43 . 0.0) (10 5030.1654977376 4019.6082579186) (10 5040.2804298643 4008.295361991) (10 5049.0200226244
3978.1292986425))
((0 . "LWPOLYLINE") (100 . "AcDbEntity") (8 . "PLANTS") (62 . 94) (370 . 13) (100 . "AcDbPolyline") (90 . 2) (70 . 0)
(43 . 0.0) (10 5037.7078054299 369.5333710407) (10 5030.1654977376 392.1578054299))
((0 . "LWPOLYLINE") (100 . "AcDbEntity") (8 . "PLANTS") (62 . 94) (370 . 13) (100 . "AcDbPolyline") (90 . 3) (70 . 0)
(43 . 0.0) (10 5030.1654977376 392.1578054299) (10 5037.7140271493 393.361199095) (10 5049.0200226244 403.4700226244))
((0 . "LWPOLYLINE") (100 . "AcDbEntity") (8 . "PLANTS") (62 . 94) (370 . 13) (100 . "AcDbPolyline") (90 . 3) (70 . 0)
(43 . 0.0) (10 5033.9366515837 3872.5494343891) (10 5037.6946832579 3857.4660633484) (10 5033.9366515837
3846.1538461538))
((0 . "LWPOLYLINE") (100 . "AcDbEntity") (8 . "PLANTS") (62 . 94) (370 . 13) (100 . "AcDbPolyline") (90 . 3) (70 . 0)
(43 . 0.0) (10 5033.9366515837 3846.1538461538) (10 5041.4846153846 3839.8100678733) (10 5071.6444570136
3834.8416289593))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5067.8733031674 3442.6845022625 0.0) (10 5093.1485994005 3409.8339036682 0.0) (10 5041.6886419425
3416.1823621233 0.0) (10 5033.9366515837 3435.1435520362 0.0))
((0 . "LWPOLYLINE") (100 . "AcDbEntity") (8 . "PLANTS") (62 . 94) (370 . 13) (100 . "AcDbPolyline") (90 . 2) (70 . 0)
(43 . 0.0) (10 5037.7078054299 1040.7239819005) (10 5037.7078054299 1010.5571266968))
((0 . "LWPOLYLINE") (100 . "AcDbEntity") (8 . "PLANTS") (62 . 94) (370 . 13) (100 . "AcDbPolyline") (90 . 2) (70 . 0)
(43 . 0.0) (10 5037.7078054299 1040.7239819005) (10 5060.332239819 1052.036199095))
((0 . "LWPOLYLINE") (100 . "AcDbEntity") (8 . "PLANTS") (62 . 94) (370 . 13) (100 . "AcDbPolyline") (90 . 2) (70 . 0)
(43 . 0.0) (10 5045.2488687783 1010.5571266968) (10 5037.7078054299 1010.5571266968))
((0 . "LWPOLYLINE") (100 . "AcDbEntity") (8 . "PLANTS") (62 . 94) (370 . 13) (100 . "AcDbPolyline") (90 . 2) (70 . 0)
(43 . 0.0) (10 5037.7078054299 369.5333710407) (10 5056.5610859729 369.5333710407))
((0 . "LWPOLYLINE") (100 . "AcDbEntity") (8 . "PLANTS") (62 . 94) (370 . 13) (100 . "AcDbPolyline") (90 . 3) (70 . 0)
(43 . 0.0) (10 5037.7078054299 324.2845022624) (10 5052.7899321267 325.4816742081) (10 5067.8733031674 335.596719457))
((0 . "LWPOLYLINE") (100 . "AcDbEntity") (8 . "PLANTS") (62 . 94) (370 . 13) (100 . "AcDbPolyline") (90 . 2) (70 . 0)
(43 . 0.0) (10 5041.4777149321 916.2895927602) (10 5060.332239819 916.2895927602))
((0 . "LWPOLYLINE") (100 . "AcDbEntity") (8 . "PLANTS") (62 . 94) (370 . 13) (100 . "AcDbPolyline") (90 . 2) (70 . 0)
(43 . 0.0) (10 5041.4777149321 916.2895927602) (10 5045.2488687783 1010.5571266968))
((0 . "LWPOLYLINE") (100 . "AcDbEntity") (8 . "PLANTS") (62 . 94) (370 . 13) (100 . "AcDbPolyline") (90 . 3) (70 . 0)
(43 . 0.0) (10 5045.2488687783 1010.5571266968) (10 5075.2665158371 1022.9264705882) (10 5090.4977375566
1040.7239819005))
((0 . "LWPOLYLINE") (100 . "AcDbEntity") (8 . "PLANTS") (62 . 94) (370 . 13) (100 . "AcDbPolyline") (90 . 2) (70 . 0)
(43 . 0.0) (10 5045.2488687783 418.5520361991) (10 5049.0200226244 403.4700226244))
((0 . "LWPOLYLINE") (100 . "AcDbEntity") (8 . "PLANTS") (62 . 94) (370 . 13) (100 . "AcDbPolyline") (90 . 2) (70 . 0)
(43 . 0.0) (10 5075.4143665158 3978.1292986425) (10 5049.0200226244 3978.1292986425))
((0 . "LWPOLYLINE") (100 . "AcDbEntity") (8 . "PLANTS") (62 . 94) (370 . 13) (100 . "AcDbPolyline") (90 . 2) (70 . 0)
(43 . 0.0) (10 5071.6444570136 3589.7433257919) (10 5049.0200226244 3612.367760181))
((0 . "LWPOLYLINE") (100 . "AcDbEntity") (8 . "PLANTS") (62 . 94) (370 . 13) (100 . "AcDbPolyline") (90 . 3) (70 . 0)
(43 . 0.0) (10 5064.1021493213 399.69739819) (10 5060.332239819 403.4700226244) (10 5049.0200226244 403.4700226244))
((0 . "LWPOLYLINE") (100 . "AcDbEntity") (8 . "PLANTS") (62 . 94) (370 . 13) (100 . "AcDbPolyline") (90 . 2) (70 . 0)
(43 . 0.0) (10 5056.5610859729 369.5333710407) (10 5067.8733031674 335.596719457))
((0 . "LWPOLYLINE") (100 . "AcDbEntity") (8 . "PLANTS") (62 . 94) (370 . 13) (100 . "AcDbPolyline") (90 . 2) (70 . 0)
(43 . 0.0) (10 5056.5610859729 369.5333710407) (10 5064.1021493213 399.69739819))
((0 . "LWPOLYLINE") (100 . "AcDbEntity") (8 . "PLANTS") (62 . 94) (370 . 13) (100 . "AcDbPolyline") (90 . 3) (70 . 0)
(43 . 0.0) (10 5060.332239819 3733.0316742081) (10 5056.8575791855 3740.5796380091) (10 5060.332239819 3766.9683257919))
((0 . "LWPOLYLINE") (100 . "AcDbEntity") (8 . "PLANTS") (62 . 94) (370 . 13) (100 . "AcDbPolyline") (90 . 2) (70 . 0)
(43 . 0.0) (10 5098.038800905 3778.2805429864) (10 5060.332239819 3766.9683257919))
((0 . "LWPOLYLINE") (100 . "AcDbEntity") (8 . "PLANTS") (62 . 94) (370 . 13) (100 . "AcDbPolyline") (90 . 3) (70 . 0)
(43 . 0.0) (10 5060.332239819 3733.0316742081) (10 5079.0308823529 3728.0632352941) (10 5082.9566742081
3721.7194570136))
((0 . "LWPOLYLINE") (100 . "AcDbEntity") (8 . "PLANTS") (62 . 94) (370 . 13) (100 . "AcDbPolyline") (90 . 2) (70 . 0)
(43 . 0.0) (10 5060.332239819 3733.0316742081) (10 5064.1021493213 3706.6360859729))
((0 . "LWPOLYLINE") (100 . "AcDbEntity") (8 . "PLANTS") (62 . 94) (370 . 13) (100 . "AcDbPolyline") (90 . 2) (70 . 0)
(43 . 0.0) (10 5060.332239819 1052.036199095) (10 5090.4977375566 1048.2664027149))
((0 . "LWPOLYLINE") (100 . "AcDbEntity") (8 . "PLANTS") (62 . 94) (370 . 13) (100 . "AcDbPolyline") (90 . 3) (70 . 0)
(43 . 0.0) (10 5067.163499575 1080.9880128457) (10 5061.3876696833 1070.8908371041) (10 5060.332239819 1052.036199095))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6596472244) (40
. 1) (40 . 1) (40 . 1) (40 . 1) (10 5060.332239819 916.2895927601 0.0) (10 5086.5059598888 885.397247781 0.0) (10
5148.5533666635 909.6234444404 0.0) (10 5204.6254300366 902.2129953152 0.0) (10 5222.4731900452 904.9773755655 0.0))
((0 . "LWPOLYLINE") (100 . "AcDbEntity") (8 . "PLANTS") (62 . 94) (370 . 13) (100 . "AcDbPolyline") (90 . 3) (70 . 0)
(43 . 0.0) (10 5060.332239819 916.2895927602) (10 5079.1792986425 933.9393665158) (10 5086.7265837104 935.1442307692))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5064.1021493213 3650.075 0.0) (10 5073.879772998 3668.8539100956 0.0) (10 5051.8006805714
3688.0038365314 0.0) (10 5064.1021493213 3706.6360859729 0.0))
((0 . "LWPOLYLINE") (100 . "AcDbEntity") (8 . "PLANTS") (62 . 94) (370 . 13) (100 . "AcDbPolyline") (90 . 3) (70 . 0)
(43 . 0.0) (10 5082.9566742081 3721.7194570136) (10 5075.2665158371 3707.8408371041) (10 5064.1021493213
3706.6360859729))
((0 . "LWPOLYLINE") (100 . "AcDbEntity") (8 . "PLANTS") (62 . 94) (370 . 13) (100 . "AcDbPolyline") (90 . 3) (70 . 0)
(43 . 0.0) (10 5086.7265837104 422.3218325792) (10 5079.1792986425 407.3882352941) (10 5064.1021493213 399.69739819))
((0 . "LWPOLYLINE") (100 . "AcDbEntity") (8 . "PLANTS") (62 . 94) (370 . 13) (100 . "AcDbPolyline") (90 . 2) (70 . 0)
(43 . 0.0) (10 5098.038800905 331.8240950226) (10 5067.8733031674 335.596719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5105.5811085973 3812.2171945701 0.0) (10 5097.7955623375 3826.6810974644 0.0) (10 5071.2227527774
3814.2311806821 0.0) (10 5071.6444570136 3834.8416289593 0.0))
((0 . "LWPOLYLINE") (100 . "AcDbEntity") (8 . "PLANTS") (62 . 94) (370 . 13) (100 . "AcDbPolyline") (90 . 3) (70 . 0)
(43 . 0.0) (10 5088.6127828054 3904.5998868778) (10 5081.9 3857.4660633484) (10 5071.6444570136 3834.8416289593))
((0 . "LWPOLYLINE") (100 . "AcDbEntity") (8 . "PLANTS") (62 . 94) (370 . 13) (100 . "AcDbPolyline") (90 . 3) (70 . 0)
(43 . 0.0) (10 5075.4143665158 3978.1292986425) (10 5079.185520362 3970.5882352941) (10 5086.7265837104
3970.5882352941))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5075.4143665158 3978.1292986425 0.0) (10 5107.398513673 3996.383105596 0.0) (10 5072.7367734265
4047.6821262711 0.0) (10 5105.5811085973 4061.0859728507 0.0))
((0 . "LWPOLYLINE") (100 . "AcDbEntity") (8 . "PLANTS") (62 . 94) (370 . 13) (100 . "AcDbPolyline") (90 . 2) (70 . 0)
(43 . 0.0) (10 5079.185520362 3518.0995475113) (10 5082.9566742081 3510.5578054299))
((0 . "LWPOLYLINE") (100 . "AcDbEntity") (8 . "PLANTS") (62 . 94) (370 . 13) (100 . "AcDbPolyline") (90 . 2) (70 . 0)
(43 . 0.0) (10 5086.7265837104 422.3218325792) (10 5079.185520362 444.9462669683))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5116.8933257919 3699.0950226244 0.0) (10 5122.1980946633 3717.2298799341 0.0) (10 5094.6547990035
3725.100214064 0.0) (10 5082.9566742081 3721.7194570136 0.0))
((0 . "LWPOLYLINE") (100 . "AcDbEntity") (8 . "PLANTS") (62 . 94) (370 . 13) (100 . "AcDbPolyline") (90 . 2) (70 . 0)
(43 . 0.0) (10 5088.6127828054 3904.5998868778) (10 5086.7265837104 3970.5882352941))
((0 . "LWPOLYLINE") (100 . "AcDbEntity") (8 . "PLANTS") (62 . 94) (370 . 13) (100 . "AcDbPolyline") (90 . 2) (70 . 0)
(43 . 0.0) (10 5124.4343891403 3981.9004524887) (10 5086.7265837104 3970.5882352941))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3568485459)
(40 . 0.5474286373) (40 . 1) (40 . 1) (40 . 1) (40 . 1) (10 5184.7666289593 999.2449095023 0.0) (10 5170.4178966309
989.6846127427 0.0) (10 5142.9259147672 987.8851770493 0.0) (10 5095.0597387523 1001.005292073 0.0) (10 5091.2982310385
949.4370303474 0.0) (10 5086.7265837104 935.1442307692 0.0))
((0 . "LWPOLYLINE") (100 . "AcDbEntity") (8 . "PLANTS") (62 . 94) (370 . 13) (100 . "AcDbPolyline") (90 . 2) (70 . 0)
(43 . 0.0) (10 5113.1221719457 938.9140271493) (10 5086.7265837104 935.1442307692))
((0 . "LWPOLYLINE") (100 . "AcDbEntity") (8 . "PLANTS") (62 . 94) (370 . 13) (100 . "AcDbPolyline") (90 . 2) (70 . 0)
(43 . 0.0) (10 5097.5197129478 490.0030547393) (10 5098.038800905 478.882918552))
((0 . "LWPOLYLINE") (100 . "AcDbEntity") (8 . "PLANTS") (62 . 94) (370 . 13) (100 . "AcDbPolyline") (90 . 2) (70 . 0)
(43 . 0.0) (10 5086.7265837104 422.3218325792) (10 5105.5811085973 422.3218325792))
((0 . "LWPOLYLINE") (100 . "AcDbEntity") (8 . "PLANTS") (62 . 94) (370 . 13) (100 . "AcDbPolyline") (90 . 3) (70 . 0)
(43 . 0.0) (10 5088.6127828054 3904.5998868778) (10 5101.8069004525 3895.3313348416) (10 5139.517760181
3891.4027149321))
((0 . "LWPOLYLINE") (100 . "AcDbEntity") (8 . "PLANTS") (62 . 94) (370 . 13) (100 . "AcDbPolyline") (90 . 3) (70 . 0)
(43 . 0.0) (10 5088.6127828054 3904.5998868778) (10 5109.1970588235 3921.5682126697) (10 5120.6632352941
3947.963800905))
((0 . "LWPOLYLINE") (100 . "AcDbEntity") (8 . "PLANTS") (62 . 94) (370 . 13) (100 . "AcDbPolyline") (90 . 2) (70 . 0)
(43 . 0.0) (10 5090.4977375566 1040.7239819005) (10 5090.4977375566 1048.2664027149))
((0 . "LWPOLYLINE") (100 . "AcDbEntity") (8 . "PLANTS") (62 . 94) (370 . 13) (100 . "AcDbPolyline") (90 . 2) (70 . 0)
(43 . 0.0) (10 5101.8099547511 1059.5786199095) (10 5090.4977375566 1048.2664027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5090.4977375566 1040.7239819005 0.0) (10 5105.3174621203 1028.0319376648 0.0) (10 5117.0060569466
1047.9955032924 0.0) (10 5116.8933257919 1059.5786199095 0.0))
((0 . "LWPOLYLINE") (100 . "AcDbEntity") (8 . "PLANTS") (62 . 94) (370 . 13) (100 . "AcDbPolyline") (90 . 3) (70 . 0)
(43 . 0.0) (10 5147.0588235294 3699.0950226244) (10 5130.9200226244 3733.0316742081) (10 5098.038800905
3778.2805429864))
((0 . "LWPOLYLINE") (100 . "AcDbEntity") (8 . "PLANTS") (62 . 94) (370 . 13) (100 . "AcDbPolyline") (90 . 3) (70 . 0)
(43 . 0.0) (10 5105.5811085973 3812.2171945701) (10 5098.1937782805 3800.9049773756) (10 5098.038800905
3778.2805429864))
((0 . "LWPOLYLINE") (100 . "AcDbEntity") (8 . "PLANTS") (62 . 94) (370 . 13) (100 . "AcDbPolyline") (90 . 2) (70 . 0)
(43 . 0.0) (10 5098.038800905 316.742081448) (10 5098.038800905 331.8240950226))
((0 . "LWPOLYLINE") (100 . "AcDbEntity") (8 . "PLANTS") (62 . 94) (370 . 13) (100 . "AcDbPolyline") (90 . 3) (70 . 0)
(43 . 0.0) (10 5158.371040724 358.2211538462) (10 5116.8933257919 357.0162895928) (10 5098.038800905 331.8240950226))
((0 . "LWPOLYLINE") (100 . "AcDbEntity") (8 . "PLANTS") (62 . 94) (370 . 13) (100 . "AcDbPolyline") (90 . 2) (70 . 0)
(43 . 0.0) (10 5098.038800905 316.742081448) (10 5113.1221719457 312.9722850679))
((0 . "LWPOLYLINE") (100 . "AcDbEntity") (8 . "PLANTS") (62 . 94) (370 . 13) (100 . "AcDbPolyline") (90 . 3) (70 . 0)
(43 . 0.0) (10 5098.038800905 316.742081448) (10 5099.2435520362 279.0356334842) (10 5113.1221719457 267.7234162896))
((0 . "LWPOLYLINE") (100 . "AcDbEntity") (8 . "PLANTS") (62 . 94) (370 . 13) (100 . "AcDbPolyline") (90 . 2) (70 . 0)
(43 . 0.0) (10 5101.8099547511 1059.5786199095) (10 5116.8933257919 1059.5786199095))
((0 . "LWPOLYLINE") (100 . "AcDbEntity") (8 . "PLANTS") (62 . 94) (370 . 13) (100 . "AcDbPolyline") (90 . 2) (70 . 0)
(43 . 0.0) (10 5105.535593983 1093.1056850188) (10 5101.8099547511 1059.5786199095))
((0 . "LWPOLYLINE") (100 . "AcDbEntity") (8 . "PLANTS") (62 . 94) (370 . 13) (100 . "AcDbPolyline") (90 . 2) (70 . 0)
(43 . 0.0) (10 5135.7466063348 3812.2171945701) (10 5105.5811085973 3812.2171945701))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7824719568) (40
. 1) (40 . 1) (40 . 1) (40 . 1) (10 5105.5811085973 422.3218325792 0.0) (10 5111.6950375634 408.0482379729 0.0) (10
5174.7657801968 393.5781791786 0.0) (10 5159.0907935472 365.6929408672 0.0) (10 5158.3710407239 358.2211538462 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5105.5811085973 422.3218325792 0.0) (10 5104.9196473479 438.750105225 0.0) (10 5120.8252795715
450.6694892601 0.0) (10 5135.7466063348 448.7188914027 0.0))
((0 . "LWPOLYLINE") (100 . "AcDbEntity") (8 . "PLANTS") (62 . 94) (370 . 13) (100 . "AcDbPolyline") (90 . 2) (70 . 0)
(43 . 0.0) (10 5113.1221719457 267.7234162896) (10 5113.1221719457 248.8687782805))
((0 . "LWPOLYLINE") (100 . "AcDbEntity") (8 . "PLANTS") (62 . 94) (370 . 13) (100 . "AcDbPolyline") (90 . 3) (70 . 0)
(43 . 0.0) (10 5143.2876696833 290.3478506787) (10 5131.9754524887 285.5195701357) (10 5113.1221719457 267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5169.6832579186 245.0989819004 0.0) (10 5152.8208675063 234.7003868855 0.0) (10 5128.9122257656
237.7676064375 0.0) (10 5113.1221719457 248.8687782805 0.0))
((0 . "LWPOLYLINE") (100 . "AcDbEntity") (8 . "PLANTS") (62 . 94) (370 . 13) (100 . "AcDbPolyline") (90 . 2) (70 . 0)
(43 . 0.0) (10 5116.8933257919 3699.0950226244) (10 5147.0588235294 3699.0950226244))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5116.8933257919 3699.0950226244 0.0) (10 5104.721161983 3682.7303467717 0.0) (10 5121.2664486123
3646.8870189458 0.0) (10 5143.5880650602 3656.3680715662 0.0))
((0 . "LWPOLYLINE") (100 . "AcDbEntity") (8 . "PLANTS") (62 . 94) (370 . 13) (100 . "AcDbPolyline") (90 . 2) (70 . 0)
(43 . 0.0) (10 5143.2876696833 1059.5786199095) (10 5116.8933257919 1059.5786199095))
((0 . "LWPOLYLINE") (100 . "AcDbEntity") (8 . "PLANTS") (62 . 94) (370 . 13) (100 . "AcDbPolyline") (90 . 2) (70 . 0)
(43 . 0.0) (10 5124.4343891403 3981.9004524887) (10 5124.4343891403 3989.4415158371))
((0 . "LWPOLYLINE") (100 . "AcDbEntity") (8 . "PLANTS") (62 . 94) (370 . 13) (100 . "AcDbPolyline") (90 . 2) (70 . 0)
(43 . 0.0) (10 5128.2055429864 3970.5882352941) (10 5124.4343891403 3981.9004524887))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5135.7466063348 3812.2171945701 0.0) (10 5151.9597092134 3776.882243362 0.0) (10 5197.9636082652
3787.1375925303 0.0) (10 5226.2443438914 3800.9049773756 0.0))
((0 . "LWPOLYLINE") (100 . "AcDbEntity") (8 . "PLANTS") (62 . 94) (370 . 13) (100 . "AcDbPolyline") (90 . 3) (70 . 0)
(43 . 0.0) (10 5135.7466063348 3812.2171945701) (10 5144.3443438914 3834.8354072398) (10 5154.5998868778
3842.3826923077))
((0 . "LWPOLYLINE") (100 . "AcDbEntity") (8 . "PLANTS") (62 . 94) (370 . 13) (100 . "AcDbPolyline") (90 . 3) (70 . 0)
(43 . 0.0) (10 5154.5998868778 3853.6949095023) (10 5144.3443438914 3865.0078054299) (10 5139.517760181
3891.4027149321))
((0 . "LWPOLYLINE") (100 . "AcDbEntity") (8 . "PLANTS") (62 . 94) (370 . 13) (100 . "AcDbPolyline") (90 . 2) (70 . 0)
(43 . 0.0) (10 5139.517760181 3891.4027149321) (10 5162.1421945701 3906.4860859729))
((0 . "LWPOLYLINE") (100 . "AcDbEntity") (8 . "PLANTS") (62 . 94) (370 . 13) (100 . "AcDbPolyline") (90 . 2) (70 . 0)
(43 . 0.0) (10 5143.2876696833 1048.2664027149) (10 5139.517760181 1033.181561086))
((0 . "LWPOLYLINE") (100 . "AcDbEntity") (8 . "PLANTS") (62 . 94) (370 . 13) (100 . "AcDbPolyline") (90 . 2) (70 . 0)
(43 . 0.0) (10 5143.2876696833 1048.2664027149) (10 5143.2876696833 1059.5786199095))
((0 . "LWPOLYLINE") (100 . "AcDbEntity") (8 . "PLANTS") (62 . 94) (370 . 13) (100 . "AcDbPolyline") (90 . 3) (70 . 0)
(43 . 0.0) (10 5173.4544117647 1089.7426470588) (10 5154.7483031674 1078.2833710407) (10 5143.2876696833
1059.5786199095))
((0 . "LWPOLYLINE") (100 . "AcDbEntity") (8 . "PLANTS") (62 . 94) (370 . 13) (100 . "AcDbPolyline") (90 . 3) (70 . 0)
(43 . 0.0) (10 5192.3076923077 1044.4937782805) (10 5180.9954751131 1050.8313348416) (10 5143.2876696833
1048.2664027149))
((0 . "LWPOLYLINE") (100 . "AcDbEntity") (8 . "PLANTS") (62 . 94) (370 . 13) (100 . "AcDbPolyline") (90 . 2) (70 . 0)
(43 . 0.0) (10 5143.2876696833 290.3478506787) (10 5169.6832579186 260.1809954751))
((0 . "LWPOLYLINE") (100 . "AcDbEntity") (8 . "PLANTS") (62 . 94) (370 . 13) (100 . "AcDbPolyline") (90 . 2) (70 . 0)
(43 . 0.0) (10 5165.9121040724 324.2845022624) (10 5143.2876696833 290.3478506787))
((0 . "LWPOLYLINE") (100 . "AcDbEntity") (8 . "PLANTS") (62 . 94) (370 . 13) (100 . "AcDbPolyline") (90 . 2) (70 . 0)
(43 . 0.0) (10 5154.5998868778 3853.6949095023) (10 5154.5998868778 3842.3826923077))
((0 . "LWPOLYLINE") (100 . "AcDbEntity") (8 . "PLANTS") (62 . 94) (370 . 13) (100 . "AcDbPolyline") (90 . 3) (70 . 0)
(43 . 0.0) (10 5154.5998868778 3853.6949095023) (10 5168.4856334842 3868.778280543) (10 5177.224321267 3887.631561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5154.5998868778 3842.3826923077 0.0) (10 5177.8698406492 3842.0602151602 0.0) (10 5230.4746067147
3836.0612752276 0.0) (10 5226.2443438914 3800.9049773756 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5222.4731900452 904.9773755656 0.0) (10 5222.2880444804 940.0513546105 0.0) (10 5184.9274829667
956.5953247276 0.0) (10 5154.5998868778 953.996040724 0.0))
((0 . "LWPOLYLINE") (100 . "AcDbEntity") (8 . "PLANTS") (62 . 94) (370 . 13) (100 . "AcDbPolyline") (90 . 2) (70 . 0)
(43 . 0.0) (10 5165.9121040724 324.2845022624) (10 5158.371040724 358.2211538462))
((0 . "LWPOLYLINE") (100 . "AcDbEntity") (8 . "PLANTS") (62 . 94) (370 . 13) (100 . "AcDbPolyline") (90 . 2) (70 . 0)
(43 . 0.0) (10 5162.1421945701 3906.4860859729) (10 5162.1421945701 3917.7983031674))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4171845378) (40
. 1) (40 . 1) (40 . 1) (40 . 1) (10 5199.8487556562 3966.817081448 0.0) (10 5193.828637034 3985.1534077294 0.0) (10
5163.3287475349 3979.9626096635 0.0) (10 5144.9726551485 3929.1234722789 0.0) (10 5162.1421945702 3917.7983031675 0.0))
((0 . "LWPOLYLINE") (100 . "AcDbEntity") (8 . "PLANTS") (62 . 94) (370 . 13) (100 . "AcDbPolyline") (90 . 2) (70 . 0)
(43 . 0.0) (10 5180.9954751131 3925.3393665158) (10 5162.1421945701 3917.7983031674))
((0 . "LWPOLYLINE") (100 . "AcDbEntity") (8 . "PLANTS") (62 . 94) (370 . 13) (100 . "AcDbPolyline") (90 . 2) (70 . 0)
(43 . 0.0) (10 5162.1421945701 3906.4860859729) (10 5177.224321267 3887.631561086))
((0 . "LWPOLYLINE") (100 . "AcDbEntity") (8 . "PLANTS") (62 . 94) (370 . 13) (100 . "AcDbPolyline") (90 . 3) (70 . 0)
(43 . 0.0) (10 5165.9121040724 324.2845022624) (10 5180.9954751131 324.1360859729) (10 5197.963800905 316.742081448))
((0 . "LWPOLYLINE") (100 . "AcDbEntity") (8 . "PLANTS") (62 . 94) (370 . 13) (100 . "AcDbPolyline") (90 . 2) (70 . 0)
(43 . 0.0) (10 5169.6832579186 245.0989819005) (10 5169.6832579186 260.1809954751))
((0 . "LWPOLYLINE") (100 . "AcDbEntity") (8 . "PLANTS") (62 . 94) (370 . 13) (100 . "AcDbPolyline") (90 . 2) (70 . 0)
(43 . 0.0) (10 5196.0788461538 279.0356334842) (10 5169.6832579186 260.1809954751))
((0 . "LWPOLYLINE") (100 . "AcDbEntity") (8 . "PLANTS") (62 . 94) (370 . 13) (100 . "AcDbPolyline") (90 . 3) (70 . 0)
(43 . 0.0) (10 5169.6832579186 245.0989819005) (10 5180.9954751131 237.711199095) (10 5211.1609728507 237.556561086))
((0 . "LWPOLYLINE") (100 . "AcDbEntity") (8 . "PLANTS") (62 . 94) (370 . 13) (100 . "AcDbPolyline") (90 . 3) (70 . 0)
(43 . 0.0) (10 5177.224321267 3887.631561086) (10 5226.2443438914 3891.4027149321) (10 5256.409841629 3887.631561086))
((0 . "LWPOLYLINE") (100 . "AcDbEntity") (8 . "PLANTS") (62 . 94) (370 . 13) (100 . "AcDbPolyline") (90 . 3) (70 . 0)
(43 . 0.0) (10 5180.9954751131 3925.3393665158) (10 5203.6199095023 3922.6248868778) (10 5263.9521493213
3951.7349547511))
((0 . "LWPOLYLINE") (100 . "AcDbEntity") (8 . "PLANTS") (62 . 94) (370 . 13) (100 . "AcDbPolyline") (90 . 3) (70 . 0)
(43 . 0.0) (10 5180.9954751131 3925.3393665158) (10 5185.8161764706 3944.1926470588) (10 5199.8487556561
3966.817081448))
((0 . "LWPOLYLINE") (100 . "AcDbEntity") (8 . "PLANTS") (62 . 94) (370 . 13) (100 . "AcDbPolyline") (90 . 3) (70 . 0)
(43 . 0.0) (10 5184.7666289593 999.2449095023) (10 5207.3910633484 988.0880090498) (10 5241.3277149321 984.1628959276))
((0 . "LWPOLYLINE") (100 . "AcDbEntity") (8 . "PLANTS") (62 . 94) (370 . 13) (100 . "AcDbPolyline") (90 . 2) (70 . 0)
(43 . 0.0) (10 5192.3076923077 1044.4937782805) (10 5184.7666289593 999.2449095023))
((0 . "LWPOLYLINE") (100 . "AcDbEntity") (8 . "PLANTS") (62 . 94) (370 . 13) (100 . "AcDbPolyline") (90 . 2) (70 . 0)
(43 . 0.0) (10 5214.9321266968 1052.036199095) (10 5192.3076923077 1044.4937782805))
((0 . "LWPOLYLINE") (100 . "AcDbEntity") (8 . "PLANTS") (62 . 94) (370 . 13) (100 . "AcDbPolyline") (90 . 2) (70 . 0)
(43 . 0.0) (10 5196.0788461538 279.0356334842) (10 5211.1609728507 267.7234162896))
((0 . "LWPOLYLINE") (100 . "AcDbEntity") (8 . "PLANTS") (62 . 94) (370 . 13) (100 . "AcDbPolyline") (90 . 2) (70 . 0)
(43 . 0.0) (10 5196.0788461538 279.0356334842) (10 5197.963800905 316.742081448))
((0 . "LWPOLYLINE") (100 . "AcDbEntity") (8 . "PLANTS") (62 . 94) (370 . 13) (100 . "AcDbPolyline") (90 . 3) (70 . 0)
(43 . 0.0) (10 5197.963800905 316.742081448) (10 5215.0867647059 350.6725113122) (10 5248.8687782805 377.0729638009))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5256.409841629 343.1363122172 0.0) (10 5250.5100834163 316.4712108499 0.0) (10 5219.3844929034
316.257505374 0.0) (10 5197.963800905 316.742081448 0.0))
((0 . "LWPOLYLINE") (100 . "AcDbEntity") (8 . "PLANTS") (62 . 94) (370 . 13) (100 . "AcDbPolyline") (90 . 2) (70 . 0)
(43 . 0.0) (10 5226.2443438914 3974.3593891403) (10 5199.8487556561 3966.817081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5216.0831306148 3733.0316742081 0.0) (10 5214.0068732542 3750.49575124 0.0) (10 5232.840632643
3762.8084498 0.0) (10 5248.8687782805 3759.4272624434 0.0))
((0 . "LWPOLYLINE") (100 . "AcDbEntity") (8 . "PLANTS") (62 . 94) (370 . 13) (100 . "AcDbPolyline") (90 . 2) (70 . 0)
(43 . 0.0) (10 5211.1609728507 267.7234162896) (10 5211.1609728507 237.556561086))
((0 . "LWPOLYLINE") (100 . "AcDbEntity") (8 . "PLANTS") (62 . 94) (370 . 13) (100 . "AcDbPolyline") (90 . 2) (70 . 0)
(43 . 0.0) (10 5256.409841629 282.8054298643) (10 5211.1609728507 267.7234162896))
((0 . "LWPOLYLINE") (100 . "AcDbEntity") (8 . "PLANTS") (62 . 94) (370 . 13) (100 . "AcDbPolyline") (90 . 3) (70 . 0)
(43 . 0.0) (10 5263.9521493213 237.556561086) (10 5248.8687782805 233.7867647059) (10 5211.1609728507 237.556561086))
((0 . "LWPOLYLINE") (100 . "AcDbEntity") (8 . "PLANTS") (62 . 94) (370 . 13) (100 . "AcDbPolyline") (90 . 3) (70 . 0)
(43 . 0.0) (10 5214.9321266968 1093.5152714932) (10 5222.4731900452 1092.3104072398) (10 5230.0154977376
1082.2030542986))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5271.4932126697 4023.3781674208 0.0) (10 5258.7380732218 4044.620464178 0.0) (10 5228.2898199068
4008.0603590509 0.0) (10 5222.4731900452 4004.5248868778 0.0))
((0 . "LWPOLYLINE") (100 . "AcDbEntity") (8 . "PLANTS") (62 . 94) (370 . 13) (100 . "AcDbPolyline") (90 . 3) (70 . 0)
(43 . 0.0) (10 5275.2643665158 912.5197963801) (10 5263.9514705882 905.1320135747) (10 5222.4731900452 904.9773755656))
((0 . "LWPOLYLINE") (100 . "AcDbEntity") (8 . "PLANTS") (62 . 94) (370 . 13) (100 . "AcDbPolyline") (90 . 2) (70 . 0)
(43 . 0.0) (10 5226.2443438914 3865.0071266968) (10 5248.8687782805 3857.4660633484))
((0 . "LWPOLYLINE") (100 . "AcDbEntity") (8 . "PLANTS") (62 . 94) (370 . 13) (100 . "AcDbPolyline") (90 . 2) (70 . 0)
(43 . 0.0) (10 5248.8687782805 3789.592760181) (10 5226.2443438914 3800.9049773756))
((0 . "LWPOLYLINE") (100 . "AcDbEntity") (8 . "PLANTS") (62 . 94) (370 . 13) (100 . "AcDbPolyline") (90 . 2) (70 . 0)
(43 . 0.0) (10 5241.3277149321 984.1628959276) (10 5290.3464932127 984.1628959276))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4772716162) (40
. 1) (40 . 1) (40 . 1) (40 . 1) (10 5241.3277149321 984.1628959276 0.0) (10 5229.1442602335 1006.3752509066 0.0) (10
5253.6858472472 1077.3842286509 0.0) (10 5312.9051779558 1020.0796750233 0.0) (10 5309.2010180995 995.4751131222 0.0))
((0 . "LWPOLYLINE") (100 . "AcDbEntity") (8 . "PLANTS") (62 . 94) (370 . 13) (100 . "AcDbPolyline") (90 . 2) (70 . 0)
(43 . 0.0) (10 5252.6399321267 3849.925) (10 5248.8687782805 3857.4660633484))
((0 . "LWPOLYLINE") (100 . "AcDbEntity") (8 . "PLANTS") (62 . 94) (370 . 13) (100 . "AcDbPolyline") (90 . 2) (70 . 0)
(43 . 0.0) (10 5248.8687782805 3857.4660633484) (10 5256.409841629 3887.631561086))
((0 . "LWPOLYLINE") (100 . "AcDbEntity") (8 . "PLANTS") (62 . 94) (370 . 13) (100 . "AcDbPolyline") (90 . 2) (70 . 0)
(43 . 0.0) (10 5248.8687782805 3789.592760181) (10 5248.8687782805 3759.4272624434))
((0 . "LWPOLYLINE") (100 . "AcDbEntity") (8 . "PLANTS") (62 . 94) (370 . 13) (100 . "AcDbPolyline") (90 . 2) (70 . 0)
(43 . 0.0) (10 5248.8687782805 3789.592760181) (10 5286.5765837104 3797.1338235294))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5248.8687782805 3759.4272624434 0.0) (10 5270.6295481638 3736.6814941978 0.0) (10 5306.826004871
3729.4711684768 0.0) (10 5335.595361991 3744.3438914027 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5305.4298642534 373.3031674208 0.0) (10 5294.0104385553 350.8807754984 0.0) (10 5260.7192558951
365.5694407865 0.0) (10 5248.8687782805 377.0729638009 0.0))
((0 . "LWPOLYLINE") (100 . "AcDbEntity") (8 . "PLANTS") (62 . 94) (370 . 13) (100 . "AcDbPolyline") (90 . 2) (70 . 0)
(43 . 0.0) (10 5248.8687782805 377.0729638009) (10 5252.6399321267 388.3851809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5373.3031674208 3800.9049773756 0.0) (10 5354.7913266157 3847.6525338889 0.0) (10 5304.7020613917
3879.7978669095 0.0) (10 5256.409841629 3887.631561086 0.0))
((0 . "LWPOLYLINE") (100 . "AcDbEntity") (8 . "PLANTS") (62 . 94) (370 . 13) (100 . "AcDbPolyline") (90 . 3) (70 . 0)
(43 . 0.0) (10 5263.9521493213 237.556561086) (10 5267.5742081448 260.1809954751) (10 5256.409841629 282.8054298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5297.888800905 309.1996606335 0.0) (10 5282.997149037 312.0139402317 0.0) (10 5255.5329505492
301.9542455696 0.0) (10 5256.409841629 282.8054298643 0.0))
((0 . "LWPOLYLINE") (100 . "AcDbEntity") (8 . "PLANTS") (62 . 94) (370 . 13) (100 . "AcDbPolyline") (90 . 3) (70 . 0)
(43 . 0.0) (10 5263.9521493213 237.556561086) (10 5275.2643665158 233.7916289593) (10 5377.074321267 233.7867647059))
((0 . "LWPOLYLINE") (100 . "AcDbEntity") (8 . "PLANTS") (62 . 94) (370 . 13) (100 . "AcDbPolyline") (90 . 3) (70 . 0)
(43 . 0.0) (10 5286.5765837104 3797.1338235294) (10 5285.3718325792 3823.5231900452) (10 5271.4932126697
3831.0704751131))
((0 . "LWPOLYLINE") (100 . "AcDbEntity") (8 . "PLANTS") (62 . 94) (370 . 13) (100 . "AcDbPolyline") (90 . 2) (70 . 0)
(43 . 0.0) (10 5275.2643665158 912.5197963801) (10 5282.8054298643 912.5197963801))
((0 . "LWPOLYLINE") (100 . "AcDbEntity") (8 . "PLANTS") (62 . 94) (370 . 13) (100 . "AcDbPolyline") (90 . 3) (70 . 0)
(43 . 0.0) (10 5275.2643665158 912.5197963801) (10 5271.6412895928 927.6018099548) (10 5290.3464932127 976.6204751131))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5279.0342760181 3917.7983031674 0.0) (10 5289.5106052626 3956.2794161848 0.0) (10 5356.8299830241
3957.6350992126 0.0) (10 5354.4498868778 3914.0271493212 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5282.8054298642 912.51979638 0.0) (10 5293.9871495598 893.8270974787 0.0) (10 5327.8198174156
893.7498026432 0.0) (10 5343.1376696833 908.7471719457 0.0))
((0 . "LWPOLYLINE") (100 . "AcDbEntity") (8 . "PLANTS") (62 . 94) (370 . 13) (100 . "AcDbPolyline") (90 . 2) (70 . 0)
(43 . 0.0) (10 5297.888800905 935.1442307692) (10 5282.8054298643 912.5197963801))
((0 . "LWPOLYLINE") (100 . "AcDbEntity") (8 . "PLANTS") (62 . 94) (370 . 13) (100 . "AcDbPolyline") (90 . 2) (70 . 0)
(43 . 0.0) (10 5324.2831447964 3793.3639140271) (10 5286.5765837104 3797.1338235294))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5290.3464932127 1097.2850678733 0.0) (10 5296.4544224437 1074.9797697641 0.0) (10 5327.34590651
1058.8273291486 0.0) (10 5346.9075791855 1078.4304298643 0.0))
((0 . "LWPOLYLINE") (100 . "AcDbEntity") (8 . "PLANTS") (62 . 94) (370 . 13) (100 . "AcDbPolyline") (90 . 2) (70 . 0)
(43 . 0.0) (10 5290.3464932127 984.1628959276) (10 5290.3464932127 976.6204751131))
((0 . "LWPOLYLINE") (100 . "AcDbEntity") (8 . "PLANTS") (62 . 94) (370 . 13) (100 . "AcDbPolyline") (90 . 2) (70 . 0)
(43 . 0.0) (10 5290.3464932127 984.1628959276) (10 5309.2010180995 995.4751131222))
((0 . "LWPOLYLINE") (100 . "AcDbEntity") (8 . "PLANTS") (62 . 94) (370 . 13) (100 . "AcDbPolyline") (90 . 3) (70 . 0)
(43 . 0.0) (10 5290.3464932127 976.6204751131) (10 5312.9709276018 970.2842760181) (10 5324.2831447964 976.6204751131))
((0 . "LWPOLYLINE") (100 . "AcDbEntity") (8 . "PLANTS") (62 . 94) (370 . 13) (100 . "AcDbPolyline") (90 . 3) (70 . 0)
(43 . 0.0) (10 5294.1176470588 335.596719457) (10 5294.1176470588 331.8240950226) (10 5301.6587104072 328.0542986425))
((0 . "LWPOLYLINE") (100 . "AcDbEntity") (8 . "PLANTS") (62 . 94) (370 . 13) (100 . "AcDbPolyline") (90 . 3) (70 . 0)
(43 . 0.0) (10 5297.888800905 309.1996606335) (10 5339.3665158371 280.2259049774) (10 5377.074321267 267.7234162896))
((0 . "LWPOLYLINE") (100 . "AcDbEntity") (8 . "PLANTS") (62 . 94) (370 . 13) (100 . "AcDbPolyline") (90 . 2) (70 . 0)
(43 . 0.0) (10 5297.888800905 309.1996606335) (10 5301.6587104072 328.0542986425))
((0 . "LWPOLYLINE") (100 . "AcDbEntity") (8 . "PLANTS") (62 . 94) (370 . 13) (100 . "AcDbPolyline") (90 . 2) (70 . 0)
(43 . 0.0) (10 5331.8254524887 343.1363122172) (10 5301.6587104072 328.0542986425))
((0 . "LWPOLYLINE") (100 . "AcDbEntity") (8 . "PLANTS") (62 . 94) (370 . 13) (100 . "AcDbPolyline") (90 . 3) (70 . 0)
(43 . 0.0) (10 5309.2010180995 995.4751131222) (10 5319.456561086 987.7856334842) (10 5324.2831447964 976.6204751131))
((0 . "LWPOLYLINE") (100 . "AcDbEntity") (8 . "PLANTS") (62 . 94) (370 . 13) (100 . "AcDbPolyline") (90 . 2) (70 . 0)
(43 . 0.0) (10 5335.595361991 3898.9437782805) (10 5312.9709276018 3917.7983031674))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5320.5132352941 388.3851809955 0.0) (10 5289.4286829734 375.9548801028 0.0) (10 5285.6942198701
434.019519956 0.0) (10 5312.9709276018 426.0944570136 0.0))
((0 . "LWPOLYLINE") (100 . "AcDbEntity") (8 . "PLANTS") (62 . 94) (370 . 13) (100 . "AcDbPolyline") (90 . 2) (70 . 0)
(43 . 0.0) (10 5320.5132352941 388.3851809955) (10 5316.742081448 380.8455882353))
((0 . "LWPOLYLINE") (100 . "AcDbEntity") (8 . "PLANTS") (62 . 94) (370 . 13) (100 . "AcDbPolyline") (90 . 2) (70 . 0)
(43 . 0.0) (10 5320.5132352941 388.3851809955) (10 5343.1376696833 392.1578054299))
((0 . "LWPOLYLINE") (100 . "AcDbEntity") (8 . "PLANTS") (62 . 94) (370 . 13) (100 . "AcDbPolyline") (90 . 2) (70 . 0)
(43 . 0.0) (10 5324.2831447964 3793.3639140271) (10 5335.595361991 3744.3438914027))
((0 . "LWPOLYLINE") (100 . "AcDbEntity") (8 . "PLANTS") (62 . 94) (370 . 13) (100 . "AcDbPolyline") (90 . 3) (70 . 0)
(43 . 0.0) (10 5324.2831447964 3793.3639140271) (10 5339.3665158371 3800.7569004525) (10 5373.3031674208
3800.9049773756))
((0 . "LWPOLYLINE") (100 . "AcDbEntity") (8 . "PLANTS") (62 . 94) (370 . 13) (100 . "AcDbPolyline") (90 . 3) (70 . 0)
(43 . 0.0) (10 5388.3865384615 970.9643665158) (10 5354.4498868778 969.2279411765) (10 5324.2831447964 976.6204751131))
((0 . "LWPOLYLINE") (100 . "AcDbEntity") (8 . "PLANTS") (62 . 94) (370 . 13) (100 . "AcDbPolyline") (90 . 3) (70 . 0)
(43 . 0.0) (10 5358.2197963801 1003.0175339367) (10 5335.7503393665 1025.6419683258) (10 5331.8254524887
1036.9541855204))
((0 . "LWPOLYLINE") (100 . "AcDbEntity") (8 . "PLANTS") (62 . 94) (370 . 13) (100 . "AcDbPolyline") (90 . 3) (70 . 0)
(43 . 0.0) (10 5356.334841629 320.5118778281) (10 5335.7503393665 329.1037330317) (10 5331.8254524887 343.1363122172))
((0 . "LWPOLYLINE") (100 . "AcDbEntity") (8 . "PLANTS") (62 . 94) (370 . 13) (100 . "AcDbPolyline") (90 . 3) (70 . 0)
(43 . 0.0) (10 5331.8254524887 343.1363122172) (10 5339.3727375566 349.4807692308) (10 5350.6787330317 350.6787330317))
((0 . "LWPOLYLINE") (100 . "AcDbEntity") (8 . "PLANTS") (62 . 94) (370 . 13) (100 . "AcDbPolyline") (90 . 3) (70 . 0)
(43 . 0.0) (10 5395.92760181 3861.2372171946) (10 5373.3031674208 3866.1987556561) (10 5335.595361991 3898.9437782805))
((0 . "LWPOLYLINE") (100 . "AcDbEntity") (8 . "PLANTS") (62 . 94) (370 . 13) (100 . "AcDbPolyline") (90 . 2) (70 . 0)
(43 . 0.0) (10 5335.595361991 3898.9437782805) (10 5354.4498868778 3914.0271493213))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5411.0109728507 3748.1150452489 0.0) (10 5387.6072278205 3739.4727278854 0.0) (10 5359.4451925189
3734.2470102232 0.0) (10 5335.595361991 3744.3438914027 0.0))
((0 . "LWPOLYLINE") (100 . "AcDbEntity") (8 . "PLANTS") (62 . 94) (370 . 13) (100 . "AcDbPolyline") (90 . 2) (70 . 0)
(43 . 0.0) (10 5343.1376696833 908.7471719457) (10 5335.595361991 931.3716063348))
((0 . "LWPOLYLINE") (100 . "AcDbEntity") (8 . "PLANTS") (62 . 94) (370 . 13) (100 . "AcDbPolyline") (90 . 2) (70 . 0)
(43 . 0.0) (10 5339.3665158371 414.782239819) (10 5343.1376696833 392.1578054299))
((0 . "LWPOLYLINE") (100 . "AcDbEntity") (8 . "PLANTS") (62 . 94) (370 . 13) (100 . "AcDbPolyline") (90 . 2) (70 . 0)
(43 . 0.0) (10 5343.1376696833 908.7471719457) (10 5365.7621040724 908.7471719457))
((0 . "LWPOLYLINE") (100 . "AcDbEntity") (8 . "PLANTS") (62 . 94) (370 . 13) (100 . "AcDbPolyline") (90 . 3) (70 . 0)
(43 . 0.0) (10 5343.1376696833 392.1578054299) (10 5357.0225113122 380.8455882353) (10 5361.9909502262 365.7607466063))
((0 . "LWPOLYLINE") (100 . "AcDbEntity") (8 . "PLANTS") (62 . 94) (370 . 13) (100 . "AcDbPolyline") (90 . 2) (70 . 0)
(43 . 0.0) (10 5361.9909502262 1055.8059954751) (10 5346.9075791855 1078.4304298643))
((0 . "LWPOLYLINE") (100 . "AcDbEntity") (8 . "PLANTS") (62 . 94) (370 . 13) (100 . "AcDbPolyline") (90 . 2) (70 . 0)
(43 . 0.0) (10 5350.6787330317 1089.7426470588) (10 5346.9075791855 1078.4304298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5399.6987556561 407.2398190045 0.0) (10 5351.9282465632 409.5264467632 0.0) (10 5373.1570640743
453.3141230385 0.0) (10 5350.6787330317 475.1131221719 0.0))
((0 . "LWPOLYLINE") (100 . "AcDbEntity") (8 . "PLANTS") (62 . 94) (370 . 13) (100 . "AcDbPolyline") (90 . 2) (70 . 0)
(43 . 0.0) (10 5365.7621040724 329.9406108597) (10 5350.6787330317 350.6787330317))
((0 . "LWPOLYLINE") (100 . "AcDbEntity") (8 . "PLANTS") (62 . 94) (370 . 13) (100 . "AcDbPolyline") (90 . 2) (70 . 0)
(43 . 0.0) (10 5350.6787330317 350.6787330317) (10 5361.9909502262 365.7607466063))
((0 . "LWPOLYLINE") (100 . "AcDbEntity") (8 . "PLANTS") (62 . 94) (370 . 13) (100 . "AcDbPolyline") (90 . 2) (70 . 0)
(43 . 0.0) (10 5369.5320135747 3910.2559954751) (10 5354.4498868778 3914.0271493213))
((0 . "LWPOLYLINE") (100 . "AcDbEntity") (8 . "PLANTS") (62 . 94) (370 . 13) (100 . "AcDbPolyline") (90 . 3) (70 . 0)
(43 . 0.0) (10 5365.7621040724 329.9406108597) (10 5361.9909502262 320.5118778281) (10 5356.334841629 320.5118778281))
((0 . "LWPOLYLINE") (100 . "AcDbEntity") (8 . "PLANTS") (62 . 94) (370 . 13) (100 . "AcDbPolyline") (90 . 2) (70 . 0)
(43 . 0.0) (10 5356.334841629 320.5118778281) (10 5384.6153846154 275.2630090498))
((0 . "LWPOLYLINE") (100 . "AcDbEntity") (8 . "PLANTS") (62 . 94) (370 . 13) (100 . "AcDbPolyline") (90 . 2) (70 . 0)
(43 . 0.0) (10 5365.7621040724 329.9406108597) (10 5356.334841629 320.5118778281))
((0 . "LWPOLYLINE") (100 . "AcDbEntity") (8 . "PLANTS") (62 . 94) (370 . 13) (100 . "AcDbPolyline") (90 . 3) (70 . 0)
(43 . 0.0) (10 5388.3865384615 328.0542986425) (10 5383.417760181 350.6725113122) (10 5361.9909502262 365.7607466063))
((0 . "LWPOLYLINE") (100 . "AcDbEntity") (8 . "PLANTS") (62 . 94) (370 . 13) (100 . "AcDbPolyline") (90 . 2) (70 . 0)
(43 . 0.0) (10 5365.7621040724 927.6018099548) (10 5365.7621040724 908.7471719457))
((0 . "LWPOLYLINE") (100 . "AcDbEntity") (8 . "PLANTS") (62 . 94) (370 . 13) (100 . "AcDbPolyline") (90 . 2) (70 . 0)
(43 . 0.0) (10 5388.3865384615 908.7471719457) (10 5365.7621040724 908.7471719457))
((0 . "LWPOLYLINE") (100 . "AcDbEntity") (8 . "PLANTS") (62 . 94) (370 . 13) (100 . "AcDbPolyline") (90 . 2) (70 . 0)
(43 . 0.0) (10 5365.7621040724 329.9406108597) (10 5388.3865384615 328.0542986425))
((0 . "LWPOLYLINE") (100 . "AcDbEntity") (8 . "PLANTS") (62 . 94) (370 . 13) (100 . "AcDbPolyline") (90 . 2) (70 . 0)
(43 . 0.0) (10 5399.6987556561 3800.9049773756) (10 5373.3031674208 3800.9049773756))
((0 . "LWPOLYLINE") (100 . "AcDbEntity") (8 . "PLANTS") (62 . 94) (370 . 13) (100 . "AcDbPolyline") (90 . 2) (70 . 0)
(43 . 0.0) (10 5377.074321267 233.7867647059) (10 5377.074321267 267.7234162896))
((0 . "LWPOLYLINE") (100 . "AcDbEntity") (8 . "PLANTS") (62 . 94) (370 . 13) (100 . "AcDbPolyline") (90 . 2) (70 . 0)
(43 . 0.0) (10 5384.6153846154 275.2630090498) (10 5377.074321267 267.7234162896))
((0 . "LWPOLYLINE") (100 . "AcDbEntity") (8 . "PLANTS") (62 . 94) (370 . 13) (100 . "AcDbPolyline") (90 . 3) (70 . 0)
(43 . 0.0) (10 5377.074321267 233.7867647059) (10 5414.7808823529 233.9400452489) (10 5437.4053167421 248.8687782805))
((0 . "LWPOLYLINE") (100 . "AcDbEntity") (8 . "PLANTS") (62 . 94) (370 . 13) (100 . "AcDbPolyline") (90 . 2) (70 . 0)
(43 . 0.0) (10 5384.6153846154 3902.7149321267) (10 5403.4686651584 3898.9437782805))
((0 . "LWPOLYLINE") (100 . "AcDbEntity") (8 . "PLANTS") (62 . 94) (370 . 13) (100 . "AcDbPolyline") (90 . 2) (70 . 0)
(43 . 0.0) (10 5399.6987556561 275.2630090498) (10 5384.6153846154 275.2630090498))
((0 . "LWPOLYLINE") (100 . "AcDbEntity") (8 . "PLANTS") (62 . 94) (370 . 13) (100 . "AcDbPolyline") (90 . 2) (70 . 0)
(43 . 0.0) (10 5388.3865384615 1025.6419683258) (10 5411.0109728507 1025.6419683258))
((0 . "LWPOLYLINE") (100 . "AcDbEntity") (8 . "PLANTS") (62 . 94) (370 . 13) (100 . "AcDbPolyline") (90 . 2) (70 . 0)
(43 . 0.0) (10 5388.3865384615 1025.6419683258) (10 5392.1564479638 999.2449095023))
((0 . "LWPOLYLINE") (100 . "AcDbEntity") (8 . "PLANTS") (62 . 94) (370 . 13) (100 . "AcDbPolyline") (90 . 3) (70 . 0)
(43 . 0.0) (10 5388.3865384615 1025.6419683258) (10 5392.3114253394 1059.571040724) (10 5399.6987556561
1067.1182126697))
((0 . "LWPOLYLINE") (100 . "AcDbEntity") (8 . "PLANTS") (62 . 94) (370 . 13) (100 . "AcDbPolyline") (90 . 2) (70 . 0)
(43 . 0.0) (10 5411.0109728507 969.0808823529) (10 5388.3865384615 970.9643665158))
((0 . "LWPOLYLINE") (100 . "AcDbEntity") (8 . "PLANTS") (62 . 94) (370 . 13) (100 . "AcDbPolyline") (90 . 3) (70 . 0)
(43 . 0.0) (10 5388.3865384615 908.7471719457) (10 5392.1564479638 927.6018099548) (10 5388.3865384615 970.9643665158))
((0 . "LWPOLYLINE") (100 . "AcDbEntity") (8 . "PLANTS") (62 . 94) (370 . 13) (100 . "AcDbPolyline") (90 . 2) (70 . 0)
(43 . 0.0) (10 5388.3865384615 970.9643665158) (10 5392.1564479638 999.2449095023))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5448.7175339367 908.7471719457 0.0) (10 5432.2018972385 903.6569256561 0.0) (10 5401.0355987566
888.226066831 0.0) (10 5388.3865384615 908.7471719457 0.0))
((0 . "LWPOLYLINE") (100 . "AcDbEntity") (8 . "PLANTS") (62 . 94) (370 . 13) (100 . "AcDbPolyline") (90 . 2) (70 . 0)
(43 . 0.0) (10 5388.3865384615 328.0542986425) (10 5411.0109728507 320.5118778281))
((0 . "LWPOLYLINE") (100 . "AcDbEntity") (8 . "PLANTS") (62 . 94) (370 . 13) (100 . "AcDbPolyline") (90 . 2) (70 . 0)
(43 . 0.0) (10 5392.1564479638 999.2449095023) (10 5411.0109728507 999.2449095023))
((0 . "LWPOLYLINE") (100 . "AcDbEntity") (8 . "PLANTS") (62 . 94) (370 . 13) (100 . "AcDbPolyline") (90 . 3) (70 . 0)
(43 . 0.0) (10 5414.7808823529 3831.0704751131) (10 5404.6665158371 3838.6190045249) (10 5395.92760181 3861.2372171946))
((0 . "LWPOLYLINE") (100 . "AcDbEntity") (8 . "PLANTS") (62 . 94) (370 . 13) (100 . "AcDbPolyline") (90 . 2) (70 . 0)
(43 . 0.0) (10 5395.92760181 3861.2372171946) (10 5407.2398190045 3868.778280543))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5399.7046052158 4050.404822309 0.0) (10 5404.6522826116 3998.8476687931 0.0) (10 5397.1323969395
3950.0939228411 0.0) (10 5403.4686651584 3898.9437782805 0.0))
((0 . "LWPOLYLINE") (100 . "AcDbEntity") (8 . "PLANTS") (62 . 94) (370 . 13) (100 . "AcDbPolyline") (90 . 3) (70 . 0)
(43 . 0.0) (10 5411.0109728507 3748.1150452489) (10 5399.8466063348 3782.0516968326) (10 5399.6987556561
3800.9049773756))
((0 . "LWPOLYLINE") (100 . "AcDbEntity") (8 . "PLANTS") (62 . 94) (370 . 13) (100 . "AcDbPolyline") (90 . 2) (70 . 0)
(43 . 0.0) (10 5399.6987556561 3800.9049773756) (10 5422.3231900452 3812.2171945701))
((0 . "LWPOLYLINE") (100 . "AcDbEntity") (8 . "PLANTS") (62 . 94) (370 . 13) (100 . "AcDbPolyline") (90 . 2) (70 . 0)
(43 . 0.0) (10 5399.6987556561 1185.8972285068) (10 5399.6987556561 1067.1182126697))
((0 . "LWPOLYLINE") (100 . "AcDbEntity") (8 . "PLANTS") (62 . 94) (370 . 13) (100 . "AcDbPolyline") (90 . 2) (70 . 0)
(43 . 0.0) (10 5418.5520361991 1048.2664027149) (10 5399.6987556561 1067.1182126697))
((0 . "LWPOLYLINE") (100 . "AcDbEntity") (8 . "PLANTS") (62 . 94) (370 . 13) (100 . "AcDbPolyline") (90 . 2) (70 . 0)
(43 . 0.0) (10 5399.6987556561 407.2398190045) (10 5399.6987556561 377.0729638009))
((0 . "LWPOLYLINE") (100 . "AcDbEntity") (8 . "PLANTS") (62 . 94) (370 . 13) (100 . "AcDbPolyline") (90 . 2) (70 . 0)
(43 . 0.0) (10 5399.6987556561 407.2398190045) (10 5433.6354072398 414.782239819))
((0 . "LWPOLYLINE") (100 . "AcDbEntity") (8 . "PLANTS") (62 . 94) (370 . 13) (100 . "AcDbPolyline") (90 . 3) (70 . 0)
(43 . 0.0) (10 5437.4053167421 256.411199095) (10 5418.5520361991 270.2883484163) (10 5399.6987556561 275.2630090498))
((0 . "LWPOLYLINE") (100 . "AcDbEntity") (8 . "PLANTS") (62 . 94) (370 . 13) (100 . "AcDbPolyline") (90 . 2) (70 . 0)
(43 . 0.0) (10 5399.6987556561 275.2630090498) (10 5403.4686651584 305.4298642534))
((0 . "LWPOLYLINE") (100 . "AcDbEntity") (8 . "PLANTS") (62 . 94) (370 . 13) (100 . "AcDbPolyline") (90 . 2) (70 . 0)
(43 . 0.0) (10 5403.4686651584 3898.9437782805) (10 5407.2398190045 3868.778280543))
((0 . "LWPOLYLINE") (100 . "AcDbEntity") (8 . "PLANTS") (62 . 94) (370 . 13) (100 . "AcDbPolyline") (90 . 3) (70 . 0)
(43 . 0.0) (10 5411.0109728507 312.9722850679) (10 5407.2398190045 312.9722850679) (10 5403.4686651584 305.4298642534))
((0 . "LWPOLYLINE") (100 . "AcDbEntity") (8 . "PLANTS") (62 . 94) (370 . 13) (100 . "AcDbPolyline") (90 . 3) (70 . 0)
(43 . 0.0) (10 5411.0109728507 312.9722850679) (10 5411.0109728507 309.1996606335) (10 5403.4686651584 305.4298642534))
((0 . "LWPOLYLINE") (100 . "AcDbEntity") (8 . "PLANTS") (62 . 94) (370 . 13) (100 . "AcDbPolyline") (90 . 2) (70 . 0)
(43 . 0.0) (10 5422.3231900452 3857.4660633484) (10 5407.2398190045 3868.778280543))
((0 . "LWPOLYLINE") (100 . "AcDbEntity") (8 . "PLANTS") (62 . 94) (370 . 13) (100 . "AcDbPolyline") (90 . 2) (70 . 0)
(43 . 0.0) (10 5407.2398190045 516.5921945701) (10 5509.0497737557 516.5921945701))
((0 . "LWPOLYLINE") (100 . "AcDbEntity") (8 . "PLANTS") (62 . 94) (370 . 13) (100 . "AcDbPolyline") (90 . 3) (70 . 0)
(43 . 0.0) (10 5411.0109728507 3748.1150452489) (10 5554.2986425339 3748.1212669683) (10 5576.9230769231
3751.8849547511))
((0 . "LWPOLYLINE") (100 . "AcDbEntity") (8 . "PLANTS") (62 . 94) (370 . 13) (100 . "AcDbPolyline") (90 . 2) (70 . 0)
(43 . 0.0) (10 5411.0109728507 1025.6419683258) (10 5411.0109728507 999.2449095023))
((0 . "LWPOLYLINE") (100 . "AcDbEntity") (8 . "PLANTS") (62 . 94) (370 . 13) (100 . "AcDbPolyline") (90 . 2) (70 . 0)
(43 . 0.0) (10 5418.5520361991 1048.2664027149) (10 5411.0109728507 1025.6419683258))
((0 . "LWPOLYLINE") (100 . "AcDbEntity") (8 . "PLANTS") (62 . 94) (370 . 13) (100 . "AcDbPolyline") (90 . 2) (70 . 0)
(43 . 0.0) (10 5411.0109728507 969.0808823529) (10 5411.0109728507 999.2449095023))
((0 . "LWPOLYLINE") (100 . "AcDbEntity") (8 . "PLANTS") (62 . 94) (370 . 13) (100 . "AcDbPolyline") (90 . 3) (70 . 0)
(43 . 0.0) (10 5448.7175339367 923.8320135747) (10 5422.471040724 946.4564479638) (10 5411.0109728507 969.0808823529))
((0 . "LWPOLYLINE") (100 . "AcDbEntity") (8 . "PLANTS") (62 . 94) (370 . 13) (100 . "AcDbPolyline") (90 . 2) (70 . 0)
(43 . 0.0) (10 5411.0109728507 312.9722850679) (10 5411.0109728507 320.5118778281))
((0 . "LWPOLYLINE") (100 . "AcDbEntity") (8 . "PLANTS") (62 . 94) (370 . 13) (100 . "AcDbPolyline") (90 . 2) (70 . 0)
(43 . 0.0) (10 5433.6354072398 324.2845022624) (10 5411.0109728507 320.5118778281))
((0 . "LWPOLYLINE") (100 . "AcDbEntity") (8 . "PLANTS") (62 . 94) (370 . 13) (100 . "AcDbPolyline") (90 . 3) (70 . 0)
(43 . 0.0) (10 5414.7808823529 3831.0704751131) (10 5415.9787330317 3819.765158371) (10 5422.3231900452
3812.2171945701))
((0 . "LWPOLYLINE") (100 . "AcDbEntity") (8 . "PLANTS") (62 . 94) (370 . 13) (100 . "AcDbPolyline") (90 . 3) (70 . 0)
(43 . 0.0) (10 5414.7808823529 3831.0704751131) (10 5421.1253393665 3838.6190045249) (10 5422.3231900452
3857.4660633484))
((0 . "LWPOLYLINE") (100 . "AcDbEntity") (8 . "PLANTS") (62 . 94) (370 . 13) (100 . "AcDbPolyline") (90 . 2) (70 . 0)
(43 . 0.0) (10 5418.5520361991 1048.2664027149) (10 5452.4886877828 1048.2664027149))
((0 . "LWPOLYLINE") (100 . "AcDbEntity") (8 . "PLANTS") (62 . 94) (370 . 13) (100 . "AcDbPolyline") (90 . 2) (70 . 0)
(43 . 0.0) (10 5422.3231900452 3857.4660633484) (10 5456.259841629 3853.6949095023))
((0 . "LWPOLYLINE") (100 . "AcDbEntity") (8 . "PLANTS") (62 . 94) (370 . 13) (100 . "AcDbPolyline") (90 . 2) (70 . 0)
(43 . 0.0) (10 5444.9476244344 3812.2171945701) (10 5422.3231900452 3812.2171945701))
((0 . "LWPOLYLINE") (100 . "AcDbEntity") (8 . "PLANTS") (62 . 94) (370 . 13) (100 . "AcDbPolyline") (90 . 3) (70 . 0)
(43 . 0.0) (10 5433.6354072398 444.9462669683) (10 5437.1093891403 433.6340497738) (10 5433.6354072398 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5433.6354072398 414.782239819 0.0) (10 5455.4406112731 382.7995235253 0.0) (10 5417.4052198327
354.7638448253 0.0) (10 5433.6354072398 324.2845022624 0.0))
((0 . "LWPOLYLINE") (100 . "AcDbEntity") (8 . "PLANTS") (62 . 94) (370 . 13) (100 . "AcDbPolyline") (90 . 2) (70 . 0)
(43 . 0.0) (10 5433.6354072398 324.2845022624) (10 5441.1764705882 320.5118778281))
((0 . "LWPOLYLINE") (100 . "AcDbEntity") (8 . "PLANTS") (62 . 94) (370 . 13) (100 . "AcDbPolyline") (90 . 2) (70 . 0)
(43 . 0.0) (10 5437.4053167421 256.411199095) (10 5437.4053167421 248.8687782805))
((0 . "LWPOLYLINE") (100 . "AcDbEntity") (8 . "PLANTS") (62 . 94) (370 . 13) (100 . "AcDbPolyline") (90 . 2) (70 . 0)
(43 . 0.0) (10 5437.4053167421 256.411199095) (10 5441.1764705882 320.5118778281))
((0 . "LWPOLYLINE") (100 . "AcDbEntity") (8 . "PLANTS") (62 . 94) (370 . 13) (100 . "AcDbPolyline") (90 . 2) (70 . 0)
(43 . 0.0) (10 5460.0297511312 248.8687782805) (10 5437.4053167421 248.8687782805))
((0 . "LWPOLYLINE") (100 . "AcDbEntity") (8 . "PLANTS") (62 . 94) (370 . 13) (100 . "AcDbPolyline") (90 . 2) (70 . 0)
(43 . 0.0) (10 5486.4253393665 324.2845022624) (10 5441.1764705882 320.5118778281))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5509.0497737557 3804.6761312217 0.0) (10 5490.7017770937 3791.7403882594 0.0) (10 5454.7420496767
3787.3050445548 0.0) (10 5444.9476244344 3812.2171945701 0.0))
((0 . "LWPOLYLINE") (100 . "AcDbEntity") (8 . "PLANTS") (62 . 94) (370 . 13) (100 . "AcDbPolyline") (90 . 3) (70 . 0)
(43 . 0.0) (10 5444.9476244344 3812.2171945701) (10 5452.3406108597 3827.3005656109) (10 5456.259841629
3853.6949095023))
((0 . "LWPOLYLINE") (100 . "AcDbEntity") (8 . "PLANTS") (62 . 94) (370 . 13) (100 . "AcDbPolyline") (90 . 2) (70 . 0)
(43 . 0.0) (10 5448.7175339367 923.8320135747) (10 5448.7175339367 908.7471719457))
((0 . "LWPOLYLINE") (100 . "AcDbEntity") (8 . "PLANTS") (62 . 94) (370 . 13) (100 . "AcDbPolyline") (90 . 3) (70 . 0)
(43 . 0.0) (10 5448.7175339367 923.8320135747) (10 5458.8259049774 935.1442307692) (10 5460.0297511312 950.2262443439))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5516.5908371041 916.2895927602 0.0) (10 5504.1063758177 890.5262738795 0.0) (10 5468.5257140843
895.4056326135 0.0) (10 5448.7175339367 908.7471719457 0.0))
((0 . "LWPOLYLINE") (100 . "AcDbEntity") (8 . "PLANTS") (62 . 94) (370 . 13) (100 . "AcDbPolyline") (90 . 2) (70 . 0)
(43 . 0.0) (10 5456.259841629 1006.7873303167) (10 5452.4886877828 1048.2664027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5452.4886877828 1048.2664027149 0.0) (10 5432.1600787695 1087.2863788666 0.0) (10 5465.5627517969
1119.9245139435 0.0) (10 5456.2529411765 1157.6201357466 0.0))
((0 . "LWPOLYLINE") (100 . "AcDbEntity") (8 . "PLANTS") (62 . 94) (370 . 13) (100 . "AcDbPolyline") (90 . 3) (70 . 0)
(43 . 0.0) (10 5509.0497737557 1052.036199095) (10 5467.5720588235 1051.8884615385) (10 5452.4886877828
1048.2664027149))
((0 . "LWPOLYLINE") (100 . "AcDbEntity") (8 . "PLANTS") (62 . 94) (370 . 13) (100 . "AcDbPolyline") (90 . 3) (70 . 0)
(43 . 0.0) (10 5456.2593891403 3868.778280543) (10 5460.0297511312 3857.4660633484) (10 5456.259841629 3853.6949095023))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5456.2593891403 3868.778280543 0.0) (10 5456.2593891403 3937.1752922323 0.0) (10 5456.2593891403
4005.5723039216 0.0) (10 5456.2593891403 4073.9693156109 0.0))
((0 . "LWPOLYLINE") (100 . "AcDbEntity") (8 . "PLANTS") (62 . 94) (370 . 13) (100 . "AcDbPolyline") (90 . 2) (70 . 0)
(43 . 0.0) (10 5456.2593891403 3868.778280543) (10 5514.7058823529 3897.0588235294))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6157.6168552036 4187.5049297452 0.0) (10 6157.6168552036 4134.0530602524 0.0) (10 6157.6168552036
4080.6011907597 0.0) (10 6157.6168552036 4027.149321267 0.0))
((0 . "LWPOLYLINE") (100 . "AcDbEntity") (8 . "PLANTS") (62 . 94) (370 . 13) (100 . "AcDbPolyline") (90 . 2) (70 . 0)
(43 . 0.0) (10 5456.259841629 1006.7873303167) (10 5509.0497737557 1006.7873303167))
((0 . "LWPOLYLINE") (100 . "AcDbEntity") (8 . "PLANTS") (62 . 94) (370 . 13) (100 . "AcDbPolyline") (90 . 3) (70 . 0)
(43 . 0.0) (10 5456.259841629 1006.7873303167) (10 5452.6433257919 984.1628959276) (10 5460.0297511312 950.2262443439))
((0 . "LWPOLYLINE") (100 . "AcDbEntity") (8 . "PLANTS") (62 . 94) (370 . 13) (100 . "AcDbPolyline") (90 . 2) (70 . 0)
(43 . 0.0) (10 5482.6541855204 950.2262443439) (10 5460.0297511312 950.2262443439))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5524.1331447964 237.556561086 0.0) (10 5504.3192274513 225.4219178323 0.0) (10 5474.86120431
231.1255164788 0.0) (10 5460.0297511312 248.8687782805 0.0))
((0 . "LWPOLYLINE") (100 . "AcDbEntity") (8 . "PLANTS") (62 . 94) (370 . 13) (100 . "AcDbPolyline") (90 . 2) (70 . 0)
(43 . 0.0) (10 5475.1131221719 267.7234162896) (10 5460.0297511312 248.8687782805))
((0 . "LWPOLYLINE") (100 . "AcDbEntity") (8 . "PLANTS") (62 . 94) (370 . 13) (100 . "AcDbPolyline") (90 . 3) (70 . 0)
(43 . 0.0) (10 5463.8009049774 392.1578054299) (10 5476.1628959276 358.2211538462) (10 5486.4253393665 343.1363122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5475.1131221719 267.7234162896 0.0) (10 5474.4123505698 279.5387773011 0.0) (10 5476.9982056082
297.1458754696 0.0) (10 5490.1964932127 301.6600678733 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5475.1131221719 267.7234162896 0.0) (10 5502.5190303861 254.0944929411 0.0) (10 5512.3688786002
297.0287903221 0.0) (10 5490.1964932127 301.6600678733 0.0))
((0 . "LWPOLYLINE") (100 . "AcDbEntity") (8 . "PLANTS") (62 . 94) (370 . 13) (100 . "AcDbPolyline") (90 . 2) (70 . 0)
(43 . 0.0) (10 5482.6541855204 950.2262443439) (10 5516.5908371041 916.2895927602))
((0 . "LWPOLYLINE") (100 . "AcDbEntity") (8 . "PLANTS") (62 . 94) (370 . 13) (100 . "AcDbPolyline") (90 . 3) (70 . 0)
(43 . 0.0) (10 5482.6541855204 950.2262443439) (10 5493.967081448 965.3082579186) (10 5509.0497737557 976.6204751131))
((0 . "LWPOLYLINE") (100 . "AcDbEntity") (8 . "PLANTS") (62 . 94) (370 . 13) (100 . "AcDbPolyline") (90 . 2) (70 . 0)
(43 . 0.0) (10 5486.4253393665 324.2845022624) (10 5486.4253393665 343.1363122172))
((0 . "LWPOLYLINE") (100 . "AcDbEntity") (8 . "PLANTS") (62 . 94) (370 . 13) (100 . "AcDbPolyline") (90 . 3) (70 . 0)
(43 . 0.0) (10 5486.4253393665 343.1363122172) (10 5497.589479638 350.8271493213) (10 5527.9030542986 392.1578054299))
((0 . "LWPOLYLINE") (100 . "AcDbEntity") (8 . "PLANTS") (62 . 94) (370 . 13) (100 . "AcDbPolyline") (90 . 2) (70 . 0)
(43 . 0.0) (10 5486.4253393665 324.2845022624) (10 5490.1964932127 301.6600678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5514.7058823529 3897.0588235294 0.0) (10 5543.17907647 3967.2143161597 0.0) (10 5485.2716978092
4026.6584924201 0.0) (10 5509.0555215845 4095.9677041293 0.0))
((0 . "LWPOLYLINE") (100 . "AcDbEntity") (8 . "PLANTS") (62 . 94) (370 . 13) (100 . "AcDbPolyline") (90 . 2) (70 . 0)
(43 . 0.0) (10 5509.0497737557 3804.6761312217) (10 5509.0497737557 3834.8416289593))
((0 . "LWPOLYLINE") (100 . "AcDbEntity") (8 . "PLANTS") (62 . 94) (370 . 13) (100 . "AcDbPolyline") (90 . 3) (70 . 0)
(43 . 0.0) (10 5509.0497737557 3834.8416289593) (10 5513.8704751131 3868.778280543) (10 5520.3619909502
3880.0904977376))
((0 . "LWPOLYLINE") (100 . "AcDbEntity") (8 . "PLANTS") (62 . 94) (370 . 13) (100 . "AcDbPolyline") (90 . 3) (70 . 0)
(43 . 0.0) (10 5550.5274886878 3861.2372171946) (10 5542.8383484163 3843.5874434389) (10 5509.0497737557
3834.8416289593))
((0 . "LWPOLYLINE") (100 . "AcDbEntity") (8 . "PLANTS") (62 . 94) (370 . 13) (100 . "AcDbPolyline") (90 . 3) (70 . 0)
(43 . 0.0) (10 5509.0497737557 3804.6761312217) (10 5539.2152714932 3793.5117647059) (10 5576.9230769231
3793.3639140271))
((0 . "LWPOLYLINE") (100 . "AcDbEntity") (8 . "PLANTS") (62 . 94) (370 . 13) (100 . "AcDbPolyline") (90 . 3) (70 . 0)
(43 . 0.0) (10 5512.8209276018 1018.0995475113) (10 5512.6725113122 1044.4889140271) (10 5509.0497737557
1052.036199095))
((0 . "LWPOLYLINE") (100 . "AcDbEntity") (8 . "PLANTS") (62 . 94) (370 . 13) (100 . "AcDbPolyline") (90 . 2) (70 . 0)
(43 . 0.0) (10 5509.0497737557 1052.036199095) (10 5509.050230594 1131.2214910378))
((0 . "LWPOLYLINE") (100 . "AcDbEntity") (8 . "PLANTS") (62 . 94) (370 . 13) (100 . "AcDbPolyline") (90 . 2) (70 . 0)
(43 . 0.0) (10 5509.0497737557 1006.7873303167) (10 5509.0497737557 976.6204751131))
((0 . "LWPOLYLINE") (100 . "AcDbEntity") (8 . "PLANTS") (62 . 94) (370 . 13) (100 . "AcDbPolyline") (90 . 2) (70 . 0)
(43 . 0.0) (10 5512.8209276018 1018.0995475113) (10 5509.0497737557 1006.7873303167))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5509.0497737557 976.6204751131 0.0) (10 5561.088603103 984.1435465522 0.0) (10 5610.8961834897
1012.9646437168 0.0) (10 5637.2553167421 1059.5786199095 0.0))
((0 . "LWPOLYLINE") (100 . "AcDbEntity") (8 . "PLANTS") (62 . 94) (370 . 13) (100 . "AcDbPolyline") (90 . 2) (70 . 0)
(43 . 0.0) (10 5512.8209276018 1018.0995475113) (10 5542.9864253394 1021.8693438914))
((0 . "LWPOLYLINE") (100 . "AcDbEntity") (8 . "PLANTS") (62 . 94) (370 . 13) (100 . "AcDbPolyline") (90 . 2) (70 . 0)
(43 . 0.0) (10 5514.7058823529 3897.0588235294) (10 5520.3619909502 3880.0904977376))
((0 . "LWPOLYLINE") (100 . "AcDbEntity") (8 . "PLANTS") (62 . 94) (370 . 13) (100 . "AcDbPolyline") (90 . 2) (70 . 0)
(43 . 0.0) (10 5514.7058823529 3897.0588235294) (10 5542.9864253394 3898.9437782805))
((0 . "LWPOLYLINE") (100 . "AcDbEntity") (8 . "PLANTS") (62 . 94) (370 . 13) (100 . "AcDbPolyline") (90 . 2) (70 . 0)
(43 . 0.0) (10 5516.5908371041 916.2895927602) (10 5558.0697963801 916.2895927602))
((0 . "LWPOLYLINE") (100 . "AcDbEntity") (8 . "PLANTS") (62 . 94) (370 . 13) (100 . "AcDbPolyline") (90 . 2) (70 . 0)
(43 . 0.0) (10 5542.9864253394 3880.0904977376) (10 5520.3619909502 3880.0904977376))
((0 . "LWPOLYLINE") (100 . "AcDbEntity") (8 . "PLANTS") (62 . 94) (370 . 13) (100 . "AcDbPolyline") (90 . 2) (70 . 0)
(43 . 0.0) (10 5520.3619909502 263.9507918552) (10 5524.1331447964 237.556561086))
((0 . "LWPOLYLINE") (100 . "AcDbEntity") (8 . "PLANTS") (62 . 94) (370 . 13) (100 . "AcDbPolyline") (90 . 2) (70 . 0)
(43 . 0.0) (10 5524.1331447964 294.1176470588) (10 5546.7575791855 301.6600678733))
((0 . "LWPOLYLINE") (100 . "AcDbEntity") (8 . "PLANTS") (62 . 94) (370 . 13) (100 . "AcDbPolyline") (90 . 3) (70 . 0)
(43 . 0.0) (10 5524.1331447964 237.556561086) (10 5569.3751131222 237.7042986425) (10 5576.9230769231 241.3263574661))
((0 . "LWPOLYLINE") (100 . "AcDbEntity") (8 . "PLANTS") (62 . 94) (370 . 13) (100 . "AcDbPolyline") (90 . 3) (70 . 0)
(43 . 0.0) (10 5535.445361991 444.9462669683) (10 5533.9281674208 437.3990950226) (10 5558.0697963801 395.92760181))
((0 . "LWPOLYLINE") (100 . "AcDbEntity") (8 . "PLANTS") (62 . 94) (370 . 13) (100 . "AcDbPolyline") (90 . 2) (70 . 0)
(43 . 0.0) (10 5542.9864253394 3880.0904977376) (10 5542.9864253394 3898.9437782805))
((0 . "LWPOLYLINE") (100 . "AcDbEntity") (8 . "PLANTS") (62 . 94) (370 . 13) (100 . "AcDbPolyline") (90 . 3) (70 . 0)
(43 . 0.0) (10 5558.0697963801 3917.7983031674) (10 5550.3799773756 3902.8695701357) (10 5542.9864253394
3898.9437782805))
((0 . "LWPOLYLINE") (100 . "AcDbEntity") (8 . "PLANTS") (62 . 94) (370 . 13) (100 . "AcDbPolyline") (90 . 2) (70 . 0)
(43 . 0.0) (10 5550.5274886878 3861.2372171946) (10 5542.9864253394 3880.0904977376))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5542.9864253394 1101.0548642534 0.0) (10 5564.5574450447 1099.7077731121 0.0) (10 5595.1283377011
1071.1068789584 0.0) (10 5573.1519230769 1052.036199095 0.0))
((0 . "LWPOLYLINE") (100 . "AcDbEntity") (8 . "PLANTS") (62 . 94) (370 . 13) (100 . "AcDbPolyline") (90 . 3) (70 . 0)
(43 . 0.0) (10 5561.8397058824 305.4298642534) (10 5558.0697963801 301.6600678733) (10 5546.7575791855 301.6600678733))
((0 . "LWPOLYLINE") (100 . "AcDbEntity") (8 . "PLANTS") (62 . 94) (370 . 13) (100 . "AcDbPolyline") (90 . 2) (70 . 0)
(43 . 0.0) (10 5546.7575791855 279.0356334842) (10 5546.7575791855 301.6600678733))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.43766989) (40 .
1) (40 . 1) (40 . 1) (40 . 1) (10 5550.5274886877 3978.1292986425 0.0) (10 5567.4652776118 3976.4272824438 0.0) (10
5583.4604080225 3955.0714527948 0.0) (10 5579.648753868 3921.3451753559 0.0) (10 5592.0064479638 3910.2559954751 0.0))
((0 . "LWPOLYLINE") (100 . "AcDbEntity") (8 . "PLANTS") (62 . 94) (370 . 13) (100 . "AcDbPolyline") (90 . 2) (70 . 0)
(43 . 0.0) (10 5550.5274886878 3861.2372171946) (10 5584.4641402715 3868.778280543))
((0 . "LWPOLYLINE") (100 . "AcDbEntity") (8 . "PLANTS") (62 . 94) (370 . 13) (100 . "AcDbPolyline") (90 . 2) (70 . 0)
(43 . 0.0) (10 5599.5475113122 912.5197963801) (10 5558.0697963801 916.2895927602))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5659.8797511313 980.3930995477 0.0) (10 5620.8921386506 1005.9520114417 0.0) (10 5560.8475035675
958.6043932809 0.0) (10 5558.0697963801 916.2895927602 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5558.0697963801 395.9276018099 0.0) (10 5550.5413472733 357.8833922711 0.0) (10 5613.682051712
343.2692519996 0.0) (10 5592.0064479637 301.6600678732 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6408865846) (40
. 1) (40 . 1) (40 . 1) (40 . 1) (10 5654.2236425338 299.7737556561 0.0) (10 5625.1791425279 316.9534951566 0.0) (10
5636.3543269673 390.7094784181 0.0) (10 5575.4933716922 409.2565541886 0.0) (10 5558.06979638 395.92760181 0.0))
((0 . "LWPOLYLINE") (100 . "AcDbEntity") (8 . "PLANTS") (62 . 94) (370 . 13) (100 . "AcDbPolyline") (90 . 2) (70 . 0)
(43 . 0.0) (10 5558.0697963801 316.742081448) (10 5561.8397058824 305.4298642534))
((0 . "LWPOLYLINE") (100 . "AcDbEntity") (8 . "PLANTS") (62 . 94) (370 . 13) (100 . "AcDbPolyline") (90 . 2) (70 . 0)
(43 . 0.0) (10 5569.3820135747 301.6600678733) (10 5561.8397058824 305.4298642534))
((0 . "LWPOLYLINE") (100 . "AcDbEntity") (8 . "PLANTS") (62 . 94) (370 . 13) (100 . "AcDbPolyline") (90 . 2) (70 . 0)
(43 . 0.0) (10 5569.3820135747 301.6600678733) (10 5592.0064479638 301.6600678733))
((0 . "LWPOLYLINE") (100 . "AcDbEntity") (8 . "PLANTS") (62 . 94) (370 . 13) (100 . "AcDbPolyline") (90 . 3) (70 . 0)
(43 . 0.0) (10 5569.3820135747 301.6600678733) (10 5569.5298642534 271.4932126697) (10 5576.9230769231 241.3263574661))
((0 . "LWPOLYLINE") (100 . "AcDbEntity") (8 . "PLANTS") (62 . 94) (370 . 13) (100 . "AcDbPolyline") (90 . 2) (70 . 0)
(43 . 0.0) (10 5576.9230769231 3793.3639140271) (10 5576.9230769231 3751.8849547511))
((0 . "LWPOLYLINE") (100 . "AcDbEntity") (8 . "PLANTS") (62 . 94) (370 . 13) (100 . "AcDbPolyline") (90 . 3) (70 . 0)
(43 . 0.0) (10 5580.6942307692 3804.6761312217) (10 5576.9230769231 3804.6761312217) (10 5576.9230769231
3793.3639140271))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5705.1286199095 3748.1150452489 0.0) (10 5662.860222739 3759.9846747105 0.0) (10 5618.7478735108
3735.5738229034 0.0) (10 5576.9230769231 3751.8849547512 0.0))
((0 . "LWPOLYLINE") (100 . "AcDbEntity") (8 . "PLANTS") (62 . 94) (370 . 13) (100 . "AcDbPolyline") (90 . 2) (70 . 0)
(43 . 0.0) (10 5576.9230769231 241.3263574661) (10 5592.0064479638 241.3263574661))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5580.6942307692 3804.6761312217 0.0) (10 5611.5621315529 3776.8047378665 0.0) (10 5662.6150430202
3792.972221622 0.0) (10 5691.9302036199 3814.1021493213 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5580.6942307692 3804.6761312217 0.0) (10 5581.546278711 3829.5173641522 0.0) (10 5612.2479165557
3836.5763492299 0.0) (10 5614.6308823529 3861.2372171946 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4478709722) (40
. 1) (40 . 1) (40 . 1) (40 . 1) (10 5573.4279840326 505.3166005176 0.0) (10 5565.7322662415 481.56829712 0.0) (10
5574.212635187 430.1109647425 0.0) (10 5630.3575962918 414.9618271548 0.0) (10 5648.5675339367 395.92760181 0.0))
((0 . "LWPOLYLINE") (100 . "AcDbEntity") (8 . "PLANTS") (62 . 94) (370 . 13) (100 . "AcDbPolyline") (90 . 3) (70 . 0)
(43 . 0.0) (10 5584.4641402715 3868.778280543) (10 5599.5475113122 3867.7285067873) (10 5614.6308823529
3861.2372171946))
((0 . "LWPOLYLINE") (100 . "AcDbEntity") (8 . "PLANTS") (62 . 94) (370 . 13) (100 . "AcDbPolyline") (90 . 3) (70 . 0)
(43 . 0.0) (10 5584.4641402715 3868.778280543) (10 5584.6125565611 3887.631561086) (10 5592.0064479638 3910.2559954751))
((0 . "LWPOLYLINE") (100 . "AcDbEntity") (8 . "PLANTS") (62 . 94) (370 . 13) (100 . "AcDbPolyline") (90 . 3) (70 . 0)
(43 . 0.0) (10 5588.2352941176 279.0356334842) (10 5594.5725113122 290.3478506787) (10 5592.0064479638 301.6600678733))
((0 . "LWPOLYLINE") (100 . "AcDbEntity") (8 . "PLANTS") (62 . 94) (370 . 13) (100 . "AcDbPolyline") (90 . 2) (70 . 0)
(43 . 0.0) (10 5592.0064479638 3910.2559954751) (10 5614.6308823529 3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5592.0064479638 241.3263574661 0.0) (10 5611.5533717841 224.2007363942 0.0) (10 5646.9856592031
224.0647679838 0.0) (10 5663.6496606335 245.0989819004 0.0))
((0 . "LWPOLYLINE") (100 . "AcDbEntity") (8 . "PLANTS") (62 . 94) (370 . 13) (100 . "AcDbPolyline") (90 . 3) (70 . 0)
(43 . 0.0) (10 5648.5675339367 279.0356334842) (10 5610.8597285068 259.131561086) (10 5592.0064479638 241.3263574661))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5599.5475113122 912.5197963801 0.0) (10 5605.5831633001 883.9558559107 0.0) (10 5651.5988477605
897.068750104 0.0) (10 5674.961877828 904.9773755656 0.0))
((0 . "LWPOLYLINE") (100 . "AcDbEntity") (8 . "PLANTS") (62 . 94) (370 . 13) (100 . "AcDbPolyline") (90 . 3) (70 . 0)
(43 . 0.0) (10 5599.5475113122 912.5197963801) (10 5648.4191176471 961.5384615385) (10 5659.8797511312 980.3930995475))
((0 . "LWPOLYLINE") (100 . "AcDbEntity") (8 . "PLANTS") (62 . 94) (370 . 13) (100 . "AcDbPolyline") (90 . 3) (70 . 0)
(43 . 0.0) (10 5625.9430995475 3898.9437782805) (10 5622.1719457014 3898.9437782805) (10 5614.6308823529
3910.2559954751))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3923585886)
(40 . 0.6814356484) (40 . 1) (40 . 1) (40 . 1) (40 . 1) (10 5693.816402715 4000.7537330316 0.0) (10 5683.9968054263
3988.9236565531 0.0) (10 5656.2647018936 3976.5804084882 0.0) (10 5620.9902067778 3949.5980615153 0.0) (10
5612.4059678818 3925.2382040312 0.0) (10 5614.6308823529 3910.2559954751 0.0))
((0 . "LWPOLYLINE") (100 . "AcDbEntity") (8 . "PLANTS") (62 . 94) (370 . 13) (100 . "AcDbPolyline") (90 . 2) (70 . 0)
(43 . 0.0) (10 5625.9430995475 3868.778280543) (10 5614.6308823529 3861.2372171946))
((0 . "LWPOLYLINE") (100 . "AcDbEntity") (8 . "PLANTS") (62 . 94) (370 . 13) (100 . "AcDbPolyline") (90 . 2) (70 . 0)
(43 . 0.0) (10 5629.7130090498 3996.9838235294) (10 5622.1719457014 3996.9838235294))
((0 . "LWPOLYLINE") (100 . "AcDbEntity") (8 . "PLANTS") (62 . 94) (370 . 13) (100 . "AcDbPolyline") (90 . 2) (70 . 0)
(43 . 0.0) (10 5625.9430995475 3868.778280543) (10 5625.9430995475 3898.9437782805))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5625.9430995475 3898.9437782805 0.0) (10 5636.5544769413 3917.2572479163 0.0) (10 5689.8102472478
3924.6543075446 0.0) (10 5678.7330316742 3887.631561086 0.0))
((0 . "LWPOLYLINE") (100 . "AcDbEntity") (8 . "PLANTS") (62 . 94) (370 . 13) (100 . "AcDbPolyline") (90 . 2) (70 . 0)
(43 . 0.0) (10 5625.9430995475 3868.778280543) (10 5644.7963800905 3868.778280543))
((0 . "LWPOLYLINE") (100 . "AcDbEntity") (8 . "PLANTS") (62 . 94) (370 . 13) (100 . "AcDbPolyline") (90 . 2) (70 . 0)
(43 . 0.0) (10 5644.7963800905 3868.778280543) (10 5691.9302036199 3814.1021493213))
((0 . "LWPOLYLINE") (100 . "AcDbEntity") (8 . "PLANTS") (62 . 94) (370 . 13) (100 . "AcDbPolyline") (90 . 2) (70 . 0)
(43 . 0.0) (10 5644.7963800905 3868.778280543) (10 5678.7330316742 3887.631561086))
((0 . "LWPOLYLINE") (100 . "AcDbEntity") (8 . "PLANTS") (62 . 94) (370 . 13) (100 . "AcDbPolyline") (90 . 2) (70 . 0)
(43 . 0.0) (10 5648.5675339367 1021.8693438914) (10 5644.7963800905 1033.181561086))
((0 . "LWPOLYLINE") (100 . "AcDbEntity") (8 . "PLANTS") (62 . 94) (370 . 13) (100 . "AcDbPolyline") (90 . 2) (70 . 0)
(43 . 0.0) (10 5671.1919683258 395.92760181) (10 5648.5675339367 395.92760181))
((0 . "LWPOLYLINE") (100 . "AcDbEntity") (8 . "PLANTS") (62 . 94) (370 . 13) (100 . "AcDbPolyline") (90 . 2) (70 . 0)
(43 . 0.0) (10 5648.5675339367 388.3851809955) (10 5648.5675339367 395.92760181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5648.5675339367 279.0356334842 0.0) (10 5664.9293194036 275.2775937774 0.0) (10 5649.9666924503
252.9289916052 0.0) (10 5663.6496606335 245.0989819005 0.0))
((0 . "LWPOLYLINE") (100 . "AcDbEntity") (8 . "PLANTS") (62 . 94) (370 . 13) (100 . "AcDbPolyline") (90 . 2) (70 . 0)
(43 . 0.0) (10 5654.2236425339 299.7737556561) (10 5648.5675339367 279.0356334842))
((0 . "LWPOLYLINE") (100 . "AcDbEntity") (8 . "PLANTS") (62 . 94) (370 . 13) (100 . "AcDbPolyline") (90 . 2) (70 . 0)
(43 . 0.0) (10 5652.3374434389 4049.7737556561) (10 5652.3374434389 4057.3148190045))
((0 . "LWPOLYLINE") (100 . "AcDbEntity") (8 . "PLANTS") (62 . 94) (370 . 13) (100 . "AcDbPolyline") (90 . 3) (70 . 0)
(43 . 0.0) (10 5652.3374434389 1082.2030542986) (10 5652.3374434389 1089.7426470588) (10 5659.8797511312
1097.2850678733))
((0 . "LWPOLYLINE") (100 . "AcDbEntity") (8 . "PLANTS") (62 . 94) (370 . 13) (100 . "AcDbPolyline") (90 . 2) (70 . 0)
(43 . 0.0) (10 5654.2236425339 299.7737556561) (10 5697.5863122172 275.2630090498))
((0 . "LWPOLYLINE") (100 . "AcDbEntity") (8 . "PLANTS") (62 . 94) (370 . 13) (100 . "AcDbPolyline") (90 . 3) (70 . 0)
(43 . 0.0) (10 5654.2236425339 299.7737556561) (10 5667.2630090498 312.9680995475) (10 5674.9618778281 328.0542986425))
((0 . "LWPOLYLINE") (100 . "AcDbEntity") (8 . "PLANTS") (62 . 94) (370 . 13) (100 . "AcDbPolyline") (90 . 2) (70 . 0)
(43 . 0.0) (10 5656.1085972851 365.7607466063) (10 5674.9618778281 343.1363122172))
((0 . "LWPOLYLINE") (100 . "AcDbEntity") (8 . "PLANTS") (62 . 94) (370 . 13) (100 . "AcDbPolyline") (90 . 3) (70 . 0)
(43 . 0.0) (10 5659.8797511312 980.3930995475) (10 5705.1279411765 988.9898190045) (10 5716.4408371041 995.4751131222))
((0 . "LWPOLYLINE") (100 . "AcDbEntity") (8 . "PLANTS") (62 . 94) (370 . 13) (100 . "AcDbPolyline") (90 . 2) (70 . 0)
(43 . 0.0) (10 5697.5863122172 245.0989819005) (10 5663.6496606335 245.0989819005))
((0 . "LWPOLYLINE") (100 . "AcDbEntity") (8 . "PLANTS") (62 . 94) (370 . 13) (100 . "AcDbPolyline") (90 . 2) (70 . 0)
(43 . 0.0) (10 5674.9618778281 904.9773755656) (10 5671.1919683258 923.8320135747))
((0 . "LWPOLYLINE") (100 . "AcDbEntity") (8 . "PLANTS") (62 . 94) (370 . 13) (100 . "AcDbPolyline") (90 . 3) (70 . 0)
(43 . 0.0) (10 5701.3574660633 392.1578054299) (10 5678.7392533937 392.3048642534) (10 5671.1919683258 395.92760181))
((0 . "LWPOLYLINE") (100 . "AcDbEntity") (8 . "PLANTS") (62 . 94) (370 . 13) (100 . "AcDbPolyline") (90 . 3) (70 . 0)
(43 . 0.0) (10 5671.1919683258 395.92760181) (10 5679.7824660633 410.8563348416) (10 5686.2740950226 414.782239819))
((0 . "LWPOLYLINE") (100 . "AcDbEntity") (8 . "PLANTS") (62 . 94) (370 . 13) (100 . "AcDbPolyline") (90 . 3) (70 . 0)
(43 . 0.0) (10 5674.9618778281 904.9773755656) (10 5716.4339366516 905.1251131222) (10 5723.9819004525 908.7471719457))
((0 . "LWPOLYLINE") (100 . "AcDbEntity") (8 . "PLANTS") (62 . 94) (370 . 13) (100 . "AcDbPolyline") (90 . 2) (70 . 0)
(43 . 0.0) (10 5674.9618778281 328.0542986425) (10 5674.9618778281 343.1363122172))
((0 . "LWPOLYLINE") (100 . "AcDbEntity") (8 . "PLANTS") (62 . 94) (370 . 13) (100 . "AcDbPolyline") (90 . 2) (70 . 0)
(43 . 0.0) (10 5674.9618778281 343.1363122172) (10 5708.8985294118 350.6787330317))
((0 . "LWPOLYLINE") (100 . "AcDbEntity") (8 . "PLANTS") (62 . 94) (370 . 13) (100 . "AcDbPolyline") (90 . 3) (70 . 0)
(43 . 0.0) (10 5674.9618778281 328.0542986425) (10 5697.5863122172 320.6671945701) (10 5712.6696832579 328.0542986425))
((0 . "LWPOLYLINE") (100 . "AcDbEntity") (8 . "PLANTS") (62 . 94) (370 . 13) (100 . "AcDbPolyline") (90 . 3) (70 . 0)
(43 . 0.0) (10 5718.3257918552 3874.4343891403) (10 5697.5863122172 3886.5820135747) (10 5678.7330316742
3887.631561086))
((0 . "LWPOLYLINE") (100 . "AcDbEntity") (8 . "PLANTS") (62 . 94) (370 . 13) (100 . "AcDbPolyline") (90 . 3) (70 . 0)
(43 . 0.0) (10 5693.8164027149 1127.4519230769) (10 5683.8498868778 1142.5339366516) (10 5686.2740950226
1153.8461538462))
((0 . "LWPOLYLINE") (100 . "AcDbEntity") (8 . "PLANTS") (62 . 94) (370 . 13) (100 . "AcDbPolyline") (90 . 3) (70 . 0)
(43 . 0.0) (10 5701.3574660633 392.1578054299) (10 5696.3890271493 407.232918552) (10 5686.2740950226 414.782239819))
((0 . "LWPOLYLINE") (100 . "AcDbEntity") (8 . "PLANTS") (62 . 94) (370 . 13) (100 . "AcDbPolyline") (90 . 2) (70 . 0)
(43 . 0.0) (10 5690.0452488688 429.8642533937) (10 5686.2740950226 414.782239819))
((0 . "LWPOLYLINE") (100 . "AcDbEntity") (8 . "PLANTS") (62 . 94) (370 . 13) (100 . "AcDbPolyline") (90 . 2) (70 . 0)
(43 . 0.0) (10 5705.1286199095 3804.6761312217) (10 5691.9302036199 3814.1021493213))
((0 . "LWPOLYLINE") (100 . "AcDbEntity") (8 . "PLANTS") (62 . 94) (370 . 13) (100 . "AcDbPolyline") (90 . 3) (70 . 0)
(43 . 0.0) (10 5718.3257918552 3874.4343891403) (10 5707.7012443439 3834.8416289593) (10 5691.9302036199
3814.1021493213))
((0 . "LWPOLYLINE") (100 . "AcDbEntity") (8 . "PLANTS") (62 . 94) (370 . 13) (100 . "AcDbPolyline") (90 . 2) (70 . 0)
(43 . 0.0) (10 5697.5863122172 245.0989819005) (10 5697.5863122172 275.2630090498))
((0 . "LWPOLYLINE") (100 . "AcDbEntity") (8 . "PLANTS") (62 . 94) (370 . 13) (100 . "AcDbPolyline") (90 . 2) (70 . 0)
(43 . 0.0) (10 5723.9819004525 305.4298642534) (10 5697.5863122172 275.2630090498))
((0 . "LWPOLYLINE") (100 . "AcDbEntity") (8 . "PLANTS") (62 . 94) (370 . 13) (100 . "AcDbPolyline") (90 . 2) (70 . 0)
(43 . 0.0) (10 5697.5863122172 245.0989819005) (10 5723.9819004525 245.0989819005))
((0 . "LWPOLYLINE") (100 . "AcDbEntity") (8 . "PLANTS") (62 . 94) (370 . 13) (100 . "AcDbPolyline") (90 . 2) (70 . 0)
(43 . 0.0) (10 5701.3574660633 3963.0471719457) (10 5731.5229638009 3914.0271493213))
((0 . "LWPOLYLINE") (100 . "AcDbEntity") (8 . "PLANTS") (62 . 94) (370 . 13) (100 . "AcDbPolyline") (90 . 2) (70 . 0)
(43 . 0.0) (10 5701.3574660633 392.1578054299) (10 5720.2107466063 373.3031674208))
((0 . "LWPOLYLINE") (100 . "AcDbEntity") (8 . "PLANTS") (62 . 94) (370 . 13) (100 . "AcDbPolyline") (90 . 2) (70 . 0)
(43 . 0.0) (10 5705.1286199095 3804.6761312217) (10 5705.1286199095 3748.1150452489))
((0 . "LWPOLYLINE") (100 . "AcDbEntity") (8 . "PLANTS") (62 . 94) (370 . 13) (100 . "AcDbPolyline") (90 . 2) (70 . 0)
(43 . 0.0) (10 5705.1286199095 3804.6761312217) (10 5757.9185520362 3808.446040724))
((0 . "LWPOLYLINE") (100 . "AcDbEntity") (8 . "PLANTS") (62 . 94) (370 . 13) (100 . "AcDbPolyline") (90 . 2) (70 . 0)
(43 . 0.0) (10 5723.9819004525 3740.5727375566) (10 5705.1286199095 3748.1150452489))
((0 . "LWPOLYLINE") (100 . "AcDbEntity") (8 . "PLANTS") (62 . 94) (370 . 13) (100 . "AcDbPolyline") (90 . 2) (70 . 0)
(43 . 0.0) (10 5712.6696832579 328.0542986425) (10 5708.8985294118 350.6787330317))
((0 . "LWPOLYLINE") (100 . "AcDbEntity") (8 . "PLANTS") (62 . 94) (370 . 13) (100 . "AcDbPolyline") (90 . 2) (70 . 0)
(43 . 0.0) (10 5720.2107466063 373.3031674208) (10 5708.8985294118 350.6787330317))
((0 . "LWPOLYLINE") (100 . "AcDbEntity") (8 . "PLANTS") (62 . 94) (370 . 13) (100 . "AcDbPolyline") (90 . 2) (70 . 0)
(43 . 0.0) (10 5723.9819004525 328.0542986425) (10 5712.6696832579 328.0542986425))
((0 . "LWPOLYLINE") (100 . "AcDbEntity") (8 . "PLANTS") (62 . 94) (370 . 13) (100 . "AcDbPolyline") (90 . 2) (70 . 0)
(43 . 0.0) (10 5716.4408371041 1018.0995475113) (10 5716.4408371041 995.4751131222))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6603880778) (40
. 1) (40 . 1) (40 . 1) (40 . 1) (10 5750.3774886878 1176.4705882352 0.0) (10 5768.3189895906 1129.8509146098 0.0) (10
5673.4631515544 1102.7913946942 0.0) (10 5695.0440172684 1031.1798383158 0.0) (10 5716.4408371042 1018.0995475112 0.0))
((0 . "LWPOLYLINE") (100 . "AcDbEntity") (8 . "PLANTS") (62 . 94) (370 . 13) (100 . "AcDbPolyline") (90 . 3) (70 . 0)
(43 . 0.0) (10 5716.4408371041 1018.0995475113) (10 5726.5483031674 1029.4117647059) (10 5735.2941176471
1055.8059954751))
((0 . "LWPOLYLINE") (100 . "AcDbEntity") (8 . "PLANTS") (62 . 94) (370 . 13) (100 . "AcDbPolyline") (90 . 2) (70 . 0)
(43 . 0.0) (10 5723.9819004525 995.4751131222) (10 5716.4408371041 995.4751131222))
((0 . "LWPOLYLINE") (100 . "AcDbEntity") (8 . "PLANTS") (62 . 94) (370 . 13) (100 . "AcDbPolyline") (90 . 3) (70 . 0)
(43 . 0.0) (10 5718.3257918552 3874.4343891403) (10 5727.6854072398 3866.2729638009) (10 5754.14739819 3861.2372171946))
((0 . "LWPOLYLINE") (100 . "AcDbEntity") (8 . "PLANTS") (62 . 94) (370 . 13) (100 . "AcDbPolyline") (90 . 3) (70 . 0)
(43 . 0.0) (10 5718.3257918552 3874.4343891403) (10 5726.4809954751 3883.7940045249) (10 5731.5229638009
3914.0271493213))
((0 . "LWPOLYLINE") (100 . "AcDbEntity") (8 . "PLANTS") (62 . 94) (370 . 13) (100 . "AcDbPolyline") (90 . 2) (70 . 0)
(43 . 0.0) (10 5720.2107466063 373.3031674208) (10 5739.0652714932 373.3031674208))
((0 . "LWPOLYLINE") (100 . "AcDbEntity") (8 . "PLANTS") (62 . 94) (370 . 13) (100 . "AcDbPolyline") (90 . 2) (70 . 0)
(43 . 0.0) (10 5723.9819004525 995.4751131222) (10 5735.2941176471 957.7686651584))
((0 . "LWPOLYLINE") (100 . "AcDbEntity") (8 . "PLANTS") (62 . 94) (370 . 13) (100 . "AcDbPolyline") (90 . 3) (70 . 0)
(43 . 0.0) (10 5761.6897058824 1010.5571266968) (10 5735.2941176471 1005.5824660633) (10 5723.9819004525
995.4751131222))
((0 . "LWPOLYLINE") (100 . "AcDbEntity") (8 . "PLANTS") (62 . 94) (370 . 13) (100 . "AcDbPolyline") (90 . 2) (70 . 0)
(43 . 0.0) (10 5735.2941176471 908.7471719457) (10 5723.9819004525 908.7471719457))
((0 . "LWPOLYLINE") (100 . "AcDbEntity") (8 . "PLANTS") (62 . 94) (370 . 13) (100 . "AcDbPolyline") (90 . 2) (70 . 0)
(43 . 0.0) (10 5723.9819004525 908.7471719457) (10 5735.2941176471 957.7686651584))
((0 . "LWPOLYLINE") (100 . "AcDbEntity") (8 . "PLANTS") (62 . 94) (370 . 13) (100 . "AcDbPolyline") (90 . 2) (70 . 0)
(43 . 0.0) (10 5723.9819004525 328.0542986425) (10 5723.9819004525 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5723.9819004525 328.0542986425 0.0) (10 5738.4377530588 337.3116964628 0.0) (10 5747.3378383295
356.8168124077 0.0) (10 5739.0652714932 373.3031674208 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5723.9819004525 305.4298642534 0.0) (10 5756.3303926927 305.9428896807 0.0) (10 5770.3929251496
245.1576513882 0.0) (10 5723.9819004525 245.0989819005 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5822.0213800905 241.3263574661 0.0) (10 5794.326925746 221.5797615099 0.0) (10 5748.1965934407
219.7279106896 0.0) (10 5723.9819004525 245.0989819004 0.0))
((0 . "LWPOLYLINE") (100 . "AcDbEntity") (8 . "PLANTS") (62 . 94) (370 . 13) (100 . "AcDbPolyline") (90 . 2) (70 . 0)
(43 . 0.0) (10 5761.6897058824 3914.0271493213) (10 5731.5229638009 3914.0271493213))
((0 . "LWPOLYLINE") (100 . "AcDbEntity") (8 . "PLANTS") (62 . 94) (370 . 13) (100 . "AcDbPolyline") (90 . 2) (70 . 0)
(43 . 0.0) (10 5756.0335972851 948.3399321267) (10 5735.2941176471 957.7686651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5735.2941176471 908.7471719457 0.0) (10 5764.3236293134 890.3376905225 0.0) (10 5814.2879878639
891.405254856 0.0) (10 5833.3335972851 923.8320135746 0.0))
((0 . "LWPOLYLINE") (100 . "AcDbEntity") (8 . "PLANTS") (62 . 94) (370 . 13) (100 . "AcDbPolyline") (90 . 2) (70 . 0)
(43 . 0.0) (10 5735.2941176471 908.7471719457) (10 5756.0335972851 948.3399321267))
((0 . "LWPOLYLINE") (100 . "AcDbEntity") (8 . "PLANTS") (62 . 94) (370 . 13) (100 . "AcDbPolyline") (90 . 3) (70 . 0)
(43 . 0.0) (10 5765.4596153846 403.4700226244) (10 5746.7609728507 392.1502262443) (10 5739.0652714932 373.3031674208))
((0 . "LWPOLYLINE") (100 . "AcDbEntity") (8 . "PLANTS") (62 . 94) (370 . 13) (100 . "AcDbPolyline") (90 . 2) (70 . 0)
(43 . 0.0) (10 5750.3774886878 1070.8908371041) (10 5765.4596153846 1082.2030542986))
((0 . "LWPOLYLINE") (100 . "AcDbEntity") (8 . "PLANTS") (62 . 94) (370 . 13) (100 . "AcDbPolyline") (90 . 2) (70 . 0)
(43 . 0.0) (10 5754.14739819 3861.2372171946) (10 5757.9185520362 3808.446040724))
((0 . "LWPOLYLINE") (100 . "AcDbEntity") (8 . "PLANTS") (62 . 94) (370 . 13) (100 . "AcDbPolyline") (90 . 2) (70 . 0)
(43 . 0.0) (10 5780.5429864253 3865.0071266968) (10 5754.14739819 3861.2372171946))
((0 . "LWPOLYLINE") (100 . "AcDbEntity") (8 . "PLANTS") (62 . 94) (370 . 13) (100 . "AcDbPolyline") (90 . 2) (70 . 0)
(43 . 0.0) (10 5756.0335972851 948.3399321267) (10 5776.7718325792 935.1442307692))
((0 . "LWPOLYLINE") (100 . "AcDbEntity") (8 . "PLANTS") (62 . 94) (370 . 13) (100 . "AcDbPolyline") (90 . 2) (70 . 0)
(43 . 0.0) (10 5756.0335972851 948.3399321267) (10 5780.5429864253 969.0808823529))
((0 . "LWPOLYLINE") (100 . "AcDbEntity") (8 . "PLANTS") (62 . 94) (370 . 13) (100 . "AcDbPolyline") (90 . 2) (70 . 0)
(43 . 0.0) (10 5806.9378959276 3804.6761312217) (10 5757.9185520362 3808.446040724))
((0 . "LWPOLYLINE") (100 . "AcDbEntity") (8 . "PLANTS") (62 . 94) (370 . 13) (100 . "AcDbPolyline") (90 . 2) (70 . 0)
(43 . 0.0) (10 5761.6897058824 3914.0271493213) (10 5761.6897058824 3929.110520362))
((0 . "SPLINE") (100 . "AcDbEntity") (8 . "PLANTS") (62 . 94) (370 . 13) (100 . "AcDbSpline") (70 . 0) (71 . 3) (72 .
13) (73 . 9) (74 . 0) (42 . 0.0000001) (43 . 0.0000001) (40 . 0.0) (40 . 0.0) (40 . 0.0) (40 . 0.0) (40 . 0.3102577822)
(40 . 0.4368970677) (40 . 0.5331941994) (40 . 0.7312444052) (40 . 0.821946402) (40 . 1) (40 . 1) (40 . 1) (40 . 1) (10
5780.5429864253 3895.1738687783 0.0) (10 5788.1240022039 3912.8967819962 0.0) (10 5845.4436527185 3903.178509986 0.0)
(10 5835.341514493 3945.1533372649 0.0) (10 5801.7421608521 3948.936753382 0.0) (10 5788.9448355098 3982.3850158662 0.0)
(10 5759.0697609364 3961.2149109088 0.0) (10 5753.5736421481 3938.6151102845 0.0) (10 5761.6897058824 3929.110520362
0.0))
((0 . "LWPOLYLINE") (100 . "AcDbEntity") (8 . "PLANTS") (62 . 94) (370 . 13) (100 . "AcDbPolyline") (90 . 2) (70 . 0)
(43 . 0.0) (10 5788.0847285068 3932.8804298643) (10 5761.6897058824 3929.110520362))
((0 . "LWPOLYLINE") (100 . "AcDbEntity") (8 . "PLANTS") (62 . 94) (370 . 13) (100 . "AcDbPolyline") (90 . 2) (70 . 0)
(43 . 0.0) (10 5780.5429864253 3895.1738687783) (10 5761.6897058824 3914.0271493213))
((0 . "LWPOLYLINE") (100 . "AcDbEntity") (8 . "PLANTS") (62 . 94) (370 . 13) (100 . "AcDbPolyline") (90 . 3) (70 . 0)
(43 . 0.0) (10 5761.6897058824 1010.5571266968) (10 5765.4596153846 1003.0175339367) (10 5773.0019230769
1003.0175339367))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5782499898) (40
. 1) (40 . 1) (40 . 1) (40 . 1) (10 5761.6897058824 1010.5571266968 0.0) (10 5760.3924923903 1028.1315707337 0.0) (10
5792.0400345552 1053.4119938041 0.0) (10 5806.7819296966 1027.1672888183 0.0) (10 5799.3969457014 1010.5571266968 0.0))
((0 . "LWPOLYLINE") (100 . "AcDbEntity") (8 . "PLANTS") (62 . 94) (370 . 13) (100 . "AcDbPolyline") (90 . 2) (70 . 0)
(43 . 0.0) (10 5765.4596153846 403.4700226244) (10 5773.0019230769 388.3851809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5765.4596153846 403.4700226244 0.0) (10 5771.1400634587 419.070825661 0.0) (10 5795.5681209179
432.4735300297 0.0) (10 5806.9378959276 411.0096153846 0.0))
((0 . "LWPOLYLINE") (100 . "AcDbEntity") (8 . "PLANTS") (62 . 94) (370 . 13) (100 . "AcDbPolyline") (90 . 3) (70 . 0)
(43 . 0.0) (10 5780.5429864253 969.0808823529) (10 5773.1497737557 984.1628959276) (10 5773.0019230769 1003.0175339367))
((0 . "LWPOLYLINE") (100 . "AcDbEntity") (8 . "PLANTS") (62 . 94) (370 . 13) (100 . "AcDbPolyline") (90 . 2) (70 . 0)
(43 . 0.0) (10 5799.3969457014 1010.5571266968) (10 5773.0019230769 1003.0175339367))
((0 . "LWPOLYLINE") (100 . "AcDbEntity") (8 . "PLANTS") (62 . 94) (370 . 13) (100 . "AcDbPolyline") (90 . 3) (70 . 0)
(43 . 0.0) (10 5787.9565943959 3733.0316742081) (10 5803.1674208145 3743.2872171946) (10 5840.8745475113
3751.8849547511))
((0 . "LWPOLYLINE") (100 . "AcDbEntity") (8 . "PLANTS") (62 . 94) (370 . 13) (100 . "AcDbPolyline") (90 . 2) (70 . 0)
(43 . 0.0) (10 5788.0847285068 328.0542986425) (10 5776.7718325792 324.2845022624))
((0 . "LWPOLYLINE") (100 . "AcDbEntity") (8 . "PLANTS") (62 . 94) (370 . 13) (100 . "AcDbPolyline") (90 . 2) (70 . 0)
(43 . 0.0) (10 5780.5429864253 3895.1738687783) (10 5780.5429864253 3865.0071266968))
((0 . "LWPOLYLINE") (100 . "AcDbEntity") (8 . "PLANTS") (62 . 94) (370 . 13) (100 . "AcDbPolyline") (90 . 3) (70 . 0)
(43 . 0.0) (10 5816.3652714932 3846.1538461538) (10 5791.8552036199 3863.809841629) (10 5780.5429864253
3865.0071266968))
((0 . "LWPOLYLINE") (100 . "AcDbEntity") (8 . "PLANTS") (62 . 94) (370 . 13) (100 . "AcDbPolyline") (90 . 3) (70 . 0)
(43 . 0.0) (10 5840.8745475113 3751.8849547511) (10 5835.9061085973 3733.0316742081) (10 5827.8596212305
3724.9849246148))
((0 . "LWPOLYLINE") (100 . "AcDbEntity") (8 . "PLANTS") (62 . 94) (370 . 13) (100 . "AcDbPolyline") (90 . 2) (70 . 0)
(43 . 0.0) (10 5780.5429864253 969.0808823529) (10 5810.7091628959 969.0808823529))
((0 . "LWPOLYLINE") (100 . "AcDbEntity") (8 . "PLANTS") (62 . 94) (370 . 13) (100 . "AcDbPolyline") (90 . 2) (70 . 0)
(43 . 0.0) (10 5803.1674208145 320.5118778281) (10 5788.0847285068 328.0542986425))
((0 . "LWPOLYLINE") (100 . "AcDbEntity") (8 . "PLANTS") (62 . 94) (370 . 13) (100 . "AcDbPolyline") (90 . 3) (70 . 0)
(43 . 0.0) (10 5803.1674208145 358.2211538462) (10 5793.0593891403 346.9089366516) (10 5788.0847285068 328.0542986425))
((0 . "LWPOLYLINE") (100 . "AcDbEntity") (8 . "PLANTS") (62 . 94) (370 . 13) (100 . "AcDbPolyline") (90 . 2) (70 . 0)
(43 . 0.0) (10 5791.8552036199 271.4932126697) (10 5822.0213800905 241.3263574661))
((0 . "LWPOLYLINE") (100 . "AcDbEntity") (8 . "PLANTS") (62 . 94) (370 . 13) (100 . "AcDbPolyline") (90 . 3) (70 . 0)
(43 . 0.0) (10 5810.7091628959 969.0808823529) (10 5806.7832579186 1003.0099547511) (10 5799.3969457014
1010.5571266968))
((0 . "LWPOLYLINE") (100 . "AcDbEntity") (8 . "PLANTS") (62 . 94) (370 . 13) (100 . "AcDbPolyline") (90 . 2) (70 . 0)
(43 . 0.0) (10 5803.1674208145 358.2211538462) (10 5818.2501131222 358.2211538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5806.9378959276 399.69739819 0.0) (10 5788.5657669649 392.7648327849 0.0) (10 5794.0577950243
369.434463985 0.0) (10 5803.1674208145 358.2211538462 0.0))
((0 . "LWPOLYLINE") (100 . "AcDbEntity") (8 . "PLANTS") (62 . 94) (370 . 13) (100 . "AcDbPolyline") (90 . 3) (70 . 0)
(43 . 0.0) (10 5803.1674208145 320.5118778281) (10 5804.3716063348 305.4298642534) (10 5818.2501131222 294.1176470588))
((0 . "LWPOLYLINE") (100 . "AcDbEntity") (8 . "PLANTS") (62 . 94) (370 . 13) (100 . "AcDbPolyline") (90 . 2) (70 . 0)
(43 . 0.0) (10 5803.1674208145 320.5118778281) (10 5822.0213800905 328.0542986425))
((0 . "LWPOLYLINE") (100 . "AcDbEntity") (8 . "PLANTS") (62 . 94) (370 . 13) (100 . "AcDbPolyline") (90 . 3) (70 . 0)
(43 . 0.0) (10 5806.9378959276 3804.6761312217) (10 5822.0213800905 3790.6494343891) (10 5859.7285067873
3770.739479638))
((0 . "LWPOLYLINE") (100 . "AcDbEntity") (8 . "PLANTS") (62 . 94) (370 . 13) (100 . "AcDbPolyline") (90 . 3) (70 . 0)
(43 . 0.0) (10 5816.3652714932 3846.1538461538) (10 5807.0856334842 3827.3005656109) (10 5806.9378959276
3804.6761312217))
((0 . "LWPOLYLINE") (100 . "AcDbEntity") (8 . "PLANTS") (62 . 94) (370 . 13) (100 . "AcDbPolyline") (90 . 2) (70 . 0)
(43 . 0.0) (10 5806.9378959276 399.69739819) (10 5806.9378959276 411.0096153846))
((0 . "LWPOLYLINE") (100 . "AcDbEntity") (8 . "PLANTS") (62 . 94) (370 . 13) (100 . "AcDbPolyline") (90 . 2) (70 . 0)
(43 . 0.0) (10 5806.9378959276 411.0096153846) (10 5829.5623303167 426.0944570136))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5806.9378959276 399.69739819 0.0) (10 5820.6513225197 391.2274238116 0.0) (10 5823.954139057
372.2952418684 0.0) (10 5818.2501131222 358.2211538462 0.0))
((0 . "LWPOLYLINE") (100 . "AcDbEntity") (8 . "PLANTS") (62 . 94) (370 . 13) (100 . "AcDbPolyline") (90 . 3) (70 . 0)
(43 . 0.0) (10 5833.3335972851 923.8320135747) (10 5821.1265837104 938.9140271493) (10 5810.7091628959 969.0808823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5816.3652714932 3846.1538461538 0.0) (10 5833.4966469128 3831.4088091388 0.0) (10 5863.4536041779
3838.5219780518 0.0) (10 5878.5824660633 3853.6949095022 0.0))
((0 . "LWPOLYLINE") (100 . "AcDbEntity") (8 . "PLANTS") (62 . 94) (370 . 13) (100 . "AcDbPolyline") (90 . 3) (70 . 0)
(43 . 0.0) (10 5816.3652714932 3846.1538461538) (10 5841.0230769231 3876.1714932127) (10 5867.2702488688
3887.631561086))
((0 . "LWPOLYLINE") (100 . "AcDbEntity") (8 . "PLANTS") (62 . 94) (370 . 13) (100 . "AcDbPolyline") (90 . 3) (70 . 0)
(43 . 0.0) (10 5818.2501131222 358.2211538462) (10 5821.8736425339 350.6718325792) (10 5822.0213800905 328.0542986425))
((0 . "LWPOLYLINE") (100 . "AcDbEntity") (8 . "PLANTS") (62 . 94) (370 . 13) (100 . "AcDbPolyline") (90 . 2) (70 . 0)
(43 . 0.0) (10 5818.2501131222 294.1176470588) (10 5840.8745475113 294.1176470588))
((0 . "LWPOLYLINE") (100 . "AcDbEntity") (8 . "PLANTS") (62 . 94) (370 . 13) (100 . "AcDbPolyline") (90 . 2) (70 . 0)
(43 . 0.0) (10 5818.2501131222 294.1176470588) (10 5818.2501131222 286.5752262443))
((0 . "LWPOLYLINE") (100 . "AcDbEntity") (8 . "PLANTS") (62 . 94) (370 . 13) (100 . "AcDbPolyline") (90 . 3) (70 . 0)
(43 . 0.0) (10 5840.8745475113 305.4298642534) (10 5829.4208144796 324.1291855204) (10 5822.0213800905 328.0542986425))
((0 . "LWPOLYLINE") (100 . "AcDbEntity") (8 . "PLANTS") (62 . 94) (370 . 13) (100 . "AcDbPolyline") (90 . 2) (70 . 0)
(43 . 0.0) (10 5848.4162895928 241.3263574661) (10 5822.0213800905 241.3263574661))
((0 . "LWPOLYLINE") (100 . "AcDbEntity") (8 . "PLANTS") (62 . 94) (370 . 13) (100 . "AcDbPolyline") (90 . 2) (70 . 0)
(43 . 0.0) (10 5852.1867647059 426.0944570136) (10 5829.5623303167 426.0944570136))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5817.8576243 480.0408102928 0.0) (10 5803.6245550216 459.4684885972 0.0) (10 5839.9466562825
448.2480479009 0.0) (10 5829.5623303167 426.0944570136 0.0))
((0 . "LWPOLYLINE") (100 . "AcDbEntity") (8 . "PLANTS") (62 . 94) (370 . 13) (100 . "AcDbPolyline") (90 . 2) (70 . 0)
(43 . 0.0) (10 5844.8349336697 3585.608675114) (10 5852.1867647059 3593.5145927602))
((0 . "LWPOLYLINE") (100 . "AcDbEntity") (8 . "PLANTS") (62 . 94) (370 . 13) (100 . "AcDbPolyline") (90 . 2) (70 . 0)
(43 . 0.0) (10 5833.3335972851 923.8320135747) (10 5840.8745475113 923.8320135747))
((0 . "LWPOLYLINE") (100 . "AcDbEntity") (8 . "PLANTS") (62 . 94) (370 . 13) (100 . "AcDbPolyline") (90 . 2) (70 . 0)
(43 . 0.0) (10 5840.8745475113 3751.8849547511) (10 5859.7285067873 3763.1971719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5840.8745475113 923.8320135746 0.0) (10 5849.9304018551 898.7413944612 0.0) (10 5897.4970707918
886.3662525842 0.0) (10 5908.7478506787 916.2895927602 0.0))
((0 . "LWPOLYLINE") (100 . "AcDbEntity") (8 . "PLANTS") (62 . 94) (370 . 13) (100 . "AcDbPolyline") (90 . 3) (70 . 0)
(43 . 0.0) (10 5886.1234162896 950.2262443439) (10 5859.7285067873 941.4866515837) (10 5840.8745475113 923.8320135747))
((0 . "LWPOLYLINE") (100 . "AcDbEntity") (8 . "PLANTS") (62 . 94) (370 . 13) (100 . "AcDbPolyline") (90 . 2) (70 . 0)
(43 . 0.0) (10 5840.8745475113 305.4298642534) (10 5855.9580316742 305.4298642534))
((0 . "LWPOLYLINE") (100 . "AcDbEntity") (8 . "PLANTS") (62 . 94) (370 . 13) (100 . "AcDbPolyline") (90 . 2) (70 . 0)
(43 . 0.0) (10 5840.8745475113 305.4298642534) (10 5840.8745475113 294.1176470588))
((0 . "LWPOLYLINE") (100 . "AcDbEntity") (8 . "PLANTS") (62 . 94) (370 . 13) (100 . "AcDbPolyline") (90 . 3) (70 . 0)
(43 . 0.0) (10 5852.1867647059 260.1809954751) (10 5842.0787330317 271.4932126697) (10 5840.8745475113 294.1176470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5908.7478506787 233.7867647059 0.0) (10 5889.3679439037 225.8654441521 0.0) (10 5864.0581506547
224.9334021343 0.0) (10 5848.4162895928 241.3263574661 0.0))
((0 . "LWPOLYLINE") (100 . "AcDbEntity") (8 . "PLANTS") (62 . 94) (370 . 13) (100 . "AcDbPolyline") (90 . 2) (70 . 0)
(43 . 0.0) (10 5852.1867647059 260.1809954751) (10 5848.4162895928 241.3263574661))
((0 . "LWPOLYLINE") (100 . "AcDbEntity") (8 . "PLANTS") (62 . 94) (370 . 13) (100 . "AcDbPolyline") (90 . 2) (70 . 0)
(43 . 0.0) (10 5852.1867647059 3623.6806561086) (10 5852.1867647059 3593.5145927602))
((0 . "LWPOLYLINE") (100 . "AcDbEntity") (8 . "PLANTS") (62 . 94) (370 . 13) (100 . "AcDbPolyline") (90 . 2) (70 . 0)
(43 . 0.0) (10 5884.2385746606 3589.7433257919) (10 5852.1867647059 3593.5145927602))
((0 . "LWPOLYLINE") (100 . "AcDbEntity") (8 . "PLANTS") (62 . 94) (370 . 13) (100 . "AcDbPolyline") (90 . 2) (70 . 0)
(43 . 0.0) (10 5852.1867647059 426.0944570136) (10 5852.1867647059 414.782239819))
((0 . "LWPOLYLINE") (100 . "AcDbEntity") (8 . "PLANTS") (62 . 94) (370 . 13) (100 . "AcDbPolyline") (90 . 3) (70 . 0)
(43 . 0.0) (10 5852.1867647059 426.0944570136) (10 5848.5647058824 475.1131221719) (10 5853.3240594631 499.3861385636))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5897.4356334842 369.5333710407 0.0) (10 5891.5671506276 386.2824364308 0.0) (10 5876.3763398596
418.0112283728 0.0) (10 5852.1867647059 414.782239819 0.0))
((0 . "LWPOLYLINE") (100 . "AcDbEntity") (8 . "PLANTS") (62 . 94) (370 . 13) (100 . "AcDbPolyline") (90 . 3) (70 . 0)
(43 . 0.0) (10 5871.0407239819 346.9089366516) (10 5853.2432126697 377.0729638009) (10 5852.1867647059 414.782239819))
((0 . "LWPOLYLINE") (100 . "AcDbEntity") (8 . "PLANTS") (62 . 94) (370 . 13) (100 . "AcDbPolyline") (90 . 2) (70 . 0)
(43 . 0.0) (10 5852.1867647059 260.1809954751) (10 5867.2702488688 282.8054298643))
((0 . "LWPOLYLINE") (100 . "AcDbEntity") (8 . "PLANTS") (62 . 94) (370 . 13) (100 . "AcDbPolyline") (90 . 2) (70 . 0)
(43 . 0.0) (10 5867.2702488688 282.8054298643) (10 5855.9580316742 305.4298642534))
((0 . "LWPOLYLINE") (100 . "AcDbEntity") (8 . "PLANTS") (62 . 94) (370 . 13) (100 . "AcDbPolyline") (90 . 3) (70 . 0)
(43 . 0.0) (10 5871.0407239819 346.9089366516) (10 5866.0660633484 320.5118778281) (10 5855.9580316742 305.4298642534))
((0 . "LWPOLYLINE") (100 . "AcDbEntity") (8 . "PLANTS") (62 . 94) (370 . 13) (100 . "AcDbPolyline") (90 . 2) (70 . 0)
(43 . 0.0) (10 5859.7285067873 3763.1971719457) (10 5859.7285067873 3770.739479638))
((0 . "LWPOLYLINE") (100 . "AcDbEntity") (8 . "PLANTS") (62 . 94) (370 . 13) (100 . "AcDbPolyline") (90 . 2) (70 . 0)
(43 . 0.0) (10 5874.811199095 3778.2805429864) (10 5859.7285067873 3770.739479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5859.7285067873 3763.1971719457 0.0) (10 5883.3046835668 3757.1305063786 0.0) (10 5873.8821555032
3713.1473530464 0.0) (10 5878.5824660633 3702.8661764706 0.0))
((0 . "LWPOLYLINE") (100 . "AcDbEntity") (8 . "PLANTS") (62 . 94) (370 . 13) (100 . "AcDbPolyline") (90 . 2) (70 . 0)
(43 . 0.0) (10 5859.7285067873 3657.6173076923) (10 5878.5824660633 3661.3872171946))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5591484393) (40
. 1) (40 . 1) (40 . 1) (40 . 1) (10 5904.9773755656 984.1628959276 0.0) (10 5906.5947210856 1004.799264293 0.0) (10
5876.2390153411 1031.1930509922 0.0) (10 5854.020919388 997.9511650057 0.0) (10 5859.7285067873 984.1628959275 0.0))
((0 . "LWPOLYLINE") (100 . "AcDbEntity") (8 . "PLANTS") (62 . 94) (370 . 13) (100 . "AcDbPolyline") (90 . 3) (70 . 0)
(43 . 0.0) (10 5878.5824660633 3853.6949095023) (10 5873.6133484163 3880.0842760181) (10 5867.2702488688
3887.631561086))
((0 . "LWPOLYLINE") (100 . "AcDbEntity") (8 . "PLANTS") (62 . 94) (370 . 13) (100 . "AcDbPolyline") (90 . 3) (70 . 0)
(43 . 0.0) (10 5889.8946832579 3902.7149321267) (10 5882.346040724 3901.5104072398) (10 5867.2702488688 3887.631561086))
((0 . "LWPOLYLINE") (100 . "AcDbEntity") (8 . "PLANTS") (62 . 94) (370 . 13) (100 . "AcDbPolyline") (90 . 2) (70 . 0)
(43 . 0.0) (10 5878.5824660633 3702.8661764706) (10 5867.2702488688 3702.8661764706))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5867.2702488688 282.8054298643 0.0) (10 5899.5567035414 275.978968968 0.0) (10 5900.8058866909
316.7548229907 0.0) (10 5923.8313348416 328.0542986425 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5897.4356334842 369.5333710407 0.0) (10 5900.7263533532 353.5846576542 0.0) (10 5883.6390233571
345.449785234 0.0) (10 5871.0407239819 346.9089366516 0.0))
((0 . "LWPOLYLINE") (100 . "AcDbEntity") (8 . "PLANTS") (62 . 94) (370 . 13) (100 . "AcDbPolyline") (90 . 3) (70 . 0)
(43 . 0.0) (10 5874.811199095 3778.2805429864) (10 5912.5191176471 3778.1324660633) (10 5927.6018099548 3770.739479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5920.0600678733 3853.6949095023 0.0) (10 5932.7067882069 3815.6761847502 0.0) (10 5865.8182105929
3819.4302379085 0.0) (10 5874.811199095 3778.2805429864 0.0))
((0 . "LWPOLYLINE") (100 . "AcDbEntity") (8 . "PLANTS") (62 . 94) (370 . 13) (100 . "AcDbPolyline") (90 . 3) (70 . 0)
(43 . 0.0) (10 5884.2385746606 3589.7433257919) (10 5882.6490950226 3555.9552036199) (10 5874.811199095
3548.2657239819))
((0 . "LWPOLYLINE") (100 . "AcDbEntity") (8 . "PLANTS") (62 . 94) (370 . 13) (100 . "AcDbPolyline") (90 . 2) (70 . 0)
(43 . 0.0) (10 5920.0600678733 3853.6949095023) (10 5878.5824660633 3853.6949095023))
((0 . "LWPOLYLINE") (100 . "AcDbEntity") (8 . "PLANTS") (62 . 94) (370 . 13) (100 . "AcDbPolyline") (90 . 2) (70 . 0)
(43 . 0.0) (10 5878.5824660633 3702.8661764706) (10 5878.5824660633 3661.3872171946))
((0 . "LWPOLYLINE") (100 . "AcDbEntity") (8 . "PLANTS") (62 . 94) (370 . 13) (100 . "AcDbPolyline") (90 . 3) (70 . 0)
(43 . 0.0) (10 5884.2385746606 3589.7433257919) (10 5885.975678733 3627.4505656109) (10 5878.5824660633
3661.3872171946))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5886.0293565163 3419.3618737632 0.0) (10 5868.2918493463 3459.6903264399 0.0) (10 5934.6878210379
3457.1941931234 0.0) (10 5908.7478506787 3499.2455882353 0.0))
((0 . "LWPOLYLINE") (100 . "AcDbEntity") (8 . "PLANTS") (62 . 94) (370 . 13) (100 . "AcDbPolyline") (90 . 2) (70 . 0)
(43 . 0.0) (10 5882.3529411765 3936.6515837104) (10 5889.8946832579 3902.7149321267))
((0 . "LWPOLYLINE") (100 . "AcDbEntity") (8 . "PLANTS") (62 . 94) (370 . 13) (100 . "AcDbPolyline") (90 . 2) (70 . 0)
(43 . 0.0) (10 5913.4299292576 3359.3690408139) (10 5912.5191176471 3363.4989819005))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5884.2385746606 3589.7433257919 0.0) (10 5897.385323997 3589.0634998254 0.0) (10 5921.7213622911
3591.0671958798 0.0) (10 5927.6018099548 3574.6606334842 0.0))
((0 . "LWPOLYLINE") (100 . "AcDbEntity") (8 . "PLANTS") (62 . 94) (370 . 13) (100 . "AcDbPolyline") (90 . 3) (70 . 0)
(43 . 0.0) (10 5886.1234162896 3491.7046380091) (10 5882.5075791855 3499.2524886878) (10 5886.1234162896
3510.5578054299))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5886.1234162896 950.2262443439 0.0) (10 5909.4617328279 947.6977825162 0.0) (10 5893.682276658
924.4052782077 0.0) (10 5908.7478506787 916.2895927602 0.0))
((0 . "LWPOLYLINE") (100 . "AcDbEntity") (8 . "PLANTS") (62 . 94) (370 . 13) (100 . "AcDbPolyline") (90 . 2) (70 . 0)
(43 . 0.0) (10 5886.1234162896 950.2262443439) (10 5904.9773755656 984.1628959276))
((0 . "LWPOLYLINE") (100 . "AcDbEntity") (8 . "PLANTS") (62 . 94) (370 . 13) (100 . "AcDbPolyline") (90 . 3) (70 . 0)
(43 . 0.0) (10 5901.2069004525 3996.9838235294) (10 5891.0987556561 3985.6716063348) (10 5889.8946832579
3974.3593891403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5931.3722850679 3898.9437782805 0.0) (10 5917.7554443856 3889.3998390463 0.0) (10 5904.7309731044
3909.9715487394 0.0) (10 5889.8946832579 3902.7149321267 0.0))
((0 . "LWPOLYLINE") (100 . "AcDbEntity") (8 . "PLANTS") (62 . 94) (370 . 13) (100 . "AcDbPolyline") (90 . 2) (70 . 0)
(43 . 0.0) (10 5897.4356334842 369.5333710407) (10 5950.2262443439 365.7607466063))
((0 . "LWPOLYLINE") (100 . "AcDbEntity") (8 . "PLANTS") (62 . 94) (370 . 13) (100 . "AcDbPolyline") (90 . 2) (70 . 0)
(43 . 0.0) (10 5904.9773755656 984.1628959276) (10 5937.0283936652 980.3930995475))
((0 . "LWPOLYLINE") (100 . "AcDbEntity") (8 . "PLANTS") (62 . 94) (370 . 13) (100 . "AcDbPolyline") (90 . 2) (70 . 0)
(43 . 0.0) (10 5908.7478506787 3744.3438914027) (10 5927.6018099548 3763.1971719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5908.7478506787 3672.6994343891 0.0) (10 5916.2399278357 3651.9747095088 0.0) (10 5927.4761940994
3610.9075052355 0.0) (10 5957.7679864253 3608.5972850679 0.0))
((0 . "LWPOLYLINE") (100 . "AcDbEntity") (8 . "PLANTS") (62 . 94) (370 . 13) (100 . "AcDbPolyline") (90 . 2) (70 . 0)
(43 . 0.0) (10 5908.7478506787 3510.5578054299) (10 5908.7478506787 3521.8700226244))
((0 . "LWPOLYLINE") (100 . "AcDbEntity") (8 . "PLANTS") (62 . 94) (370 . 13) (100 . "AcDbPolyline") (90 . 2) (70 . 0)
(43 . 0.0) (10 5938.9140271493 916.2895927602) (10 5908.7478506787 916.2895927602))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5908.7478506787 233.7867647059 0.0) (10 5929.3251380461 225.5571110907 0.0) (10 5956.0998102075
224.3218519953 0.0) (10 5972.850678733 241.3263574661 0.0))
((0 . "LWPOLYLINE") (100 . "AcDbEntity") (8 . "PLANTS") (62 . 94) (370 . 13) (100 . "AcDbPolyline") (90 . 2) (70 . 0)
(43 . 0.0) (10 5908.7478506787 233.7867647059) (10 5912.5191176471 252.6385746606))
((0 . "LWPOLYLINE") (100 . "AcDbEntity") (8 . "PLANTS") (62 . 94) (370 . 13) (100 . "AcDbPolyline") (90 . 2) (70 . 0)
(43 . 0.0) (10 5927.6018099548 3706.6360859729) (10 5912.5191176471 3710.407239819))
((0 . "LWPOLYLINE") (100 . "AcDbEntity") (8 . "PLANTS") (62 . 94) (370 . 13) (100 . "AcDbPolyline") (90 . 2) (70 . 0)
(43 . 0.0) (10 5916.2895927602 3555.8066742081) (10 5927.6018099548 3574.6606334842))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5241846604)
(40 . 0.9086515132) (40 . 1) (40 . 1) (40 . 1) (40 . 1) (10 5920.0600678733 3853.6949095022 0.0) (10 5934.7876315687
3872.0536184218 0.0) (10 5969.1039748427 3860.6155607188 0.0) (10 5999.7073790717 3847.0663450474 0.0) (10
6015.7546784275 3841.1182219417 0.0) (10 6018.0995475114 3838.6127828055 0.0))
((0 . "LWPOLYLINE") (100 . "AcDbEntity") (8 . "PLANTS") (62 . 94) (370 . 13) (100 . "AcDbPolyline") (90 . 2) (70 . 0)
(43 . 0.0) (10 5923.8313348416 448.7188914027) (10 5931.3722850679 441.1764705882))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5923.8313348417 448.7188914028 0.0) (10 5880.1267904759 451.8078409368 0.0) (10 5916.6513413162
385.6815321451 0.0) (10 5946.4557692308 414.782239819 0.0))
((0 . "LWPOLYLINE") (100 . "AcDbEntity") (8 . "PLANTS") (62 . 94) (370 . 13) (100 . "AcDbPolyline") (90 . 3) (70 . 0)
(43 . 0.0) (10 5923.8313348416 448.7188914027) (10 5931.3722850679 460.0311085973) (10 5935.1435520362 460.0311085973))
((0 . "LWPOLYLINE") (100 . "AcDbEntity") (8 . "PLANTS") (62 . 94) (370 . 13) (100 . "AcDbPolyline") (90 . 2) (70 . 0)
(43 . 0.0) (10 5923.8313348416 328.0542986425) (10 5923.8313348416 339.3665158371))
((0 . "LWPOLYLINE") (100 . "AcDbEntity") (8 . "PLANTS") (62 . 94) (370 . 13) (100 . "AcDbPolyline") (90 . 3) (70 . 0)
(43 . 0.0) (10 5969.0802036199 294.1176470588) (10 5935.1435520362 323.2273755656) (10 5923.8313348416 328.0542986425))
((0 . "LWPOLYLINE") (100 . "AcDbEntity") (8 . "PLANTS") (62 . 94) (370 . 13) (100 . "AcDbPolyline") (90 . 3) (70 . 0)
(43 . 0.0) (10 5969.0802036199 267.7234162896) (10 5927.7564479638 272.6980769231) (10 5923.8313348416 282.8054298643))
((0 . "LWPOLYLINE") (100 . "AcDbEntity") (8 . "PLANTS") (62 . 94) (370 . 13) (100 . "AcDbPolyline") (90 . 2) (70 . 0)
(43 . 0.0) (10 5927.6018099548 3770.739479638) (10 5927.6018099548 3763.1971719457))
((0 . "LWPOLYLINE") (100 . "AcDbEntity") (8 . "PLANTS") (62 . 94) (370 . 13) (100 . "AcDbPolyline") (90 . 2) (70 . 0)
(43 . 0.0) (10 5927.6018099548 3770.739479638) (10 5942.6845022624 3774.5093891403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5927.6018099548 3763.1971719457 0.0) (10 5943.442003102 3751.4920687426 0.0) (10 5932.5472935226
3727.5920551569 0.0) (10 5946.4557692308 3714.1783936652 0.0))
((0 . "LWPOLYLINE") (100 . "AcDbEntity") (8 . "PLANTS") (62 . 94) (370 . 13) (100 . "AcDbPolyline") (90 . 2) (70 . 0)
(43 . 0.0) (10 5927.6018099548 3706.6360859729) (10 5927.6018099548 3691.553959276))
((0 . "LWPOLYLINE") (100 . "AcDbEntity") (8 . "PLANTS") (62 . 94) (370 . 13) (100 . "AcDbPolyline") (90 . 2) (70 . 0)
(43 . 0.0) (10 5927.6018099548 3706.6360859729) (10 5946.4557692308 3714.1783936652))
((0 . "LWPOLYLINE") (100 . "AcDbEntity") (8 . "PLANTS") (62 . 94) (370 . 13) (100 . "AcDbPolyline") (90 . 2) (70 . 0)
(43 . 0.0) (10 5938.9140271493 3574.6606334842) (10 5927.6018099548 3574.6606334842))
((0 . "LWPOLYLINE") (100 . "AcDbEntity") (8 . "PLANTS") (62 . 94) (370 . 13) (100 . "AcDbPolyline") (90 . 3) (70 . 0)
(43 . 0.0) (10 5980.3924208145 3921.5682126697) (10 5961.5384615385 3932.7325791855) (10 5931.3722850679
3925.3393665158))
((0 . "LWPOLYLINE") (100 . "AcDbEntity") (8 . "PLANTS") (62 . 94) (370 . 13) (100 . "AcDbPolyline") (90 . 2) (70 . 0)
(43 . 0.0) (10 5935.1435520362 3503.0168552036) (10 5957.7679864253 3480.3924208145))
((0 . "LWPOLYLINE") (100 . "AcDbEntity") (8 . "PLANTS") (62 . 94) (370 . 13) (100 . "AcDbPolyline") (90 . 2) (70 . 0)
(43 . 0.0) (10 5935.1435520362 1006.7873303167) (10 5937.0283936652 980.3930995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5935.1435520362 1006.7873303167 0.0) (10 5913.8240392092 1015.6788127661 0.0) (10 5906.1398714649
1053.4818051555 0.0) (10 5942.6845022624 1059.5786199095 0.0))
((0 . "LWPOLYLINE") (100 . "AcDbEntity") (8 . "PLANTS") (62 . 94) (370 . 13) (100 . "AcDbPolyline") (90 . 3) (70 . 0)
(43 . 0.0) (10 5935.1435520362 1006.7873303167) (10 5952.7926470588 1029.4117647059) (10 5950.2262443439
1052.036199095))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5935.1435520362 460.0311085973 0.0) (10 5949.4950990422 454.8512321106 0.0) (10 5976.6277625142
424.6785336905 0.0) (10 5946.4557692308 414.782239819 0.0))
((0 . "LWPOLYLINE") (100 . "AcDbEntity") (8 . "PLANTS") (62 . 94) (370 . 13) (100 . "AcDbPolyline") (90 . 2) (70 . 0)
(43 . 0.0) (10 5938.9140271493 467.5707013575) (10 5935.1435520362 460.0311085973))
((0 . "LWPOLYLINE") (100 . "AcDbEntity") (8 . "PLANTS") (62 . 94) (370 . 13) (100 . "AcDbPolyline") (90 . 2) (70 . 0)
(43 . 0.0) (10 5978.5067873303 980.3930995475) (10 5937.0283936652 980.3930995475))
((0 . "LWPOLYLINE") (100 . "AcDbEntity") (8 . "PLANTS") (62 . 94) (370 . 13) (100 . "AcDbPolyline") (90 . 2) (70 . 0)
(43 . 0.0) (10 5942.6845022624 927.6018099548) (10 5937.0283936652 980.3930995475))
((0 . "LWPOLYLINE") (100 . "AcDbEntity") (8 . "PLANTS") (62 . 94) (370 . 13) (100 . "AcDbPolyline") (90 . 3) (70 . 0)
(43 . 0.0) (10 5938.9140271493 3676.4705882353) (10 5953.996719457 3658.8211538462) (10 5995.4751131222
3657.6173076923))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5938.9140271493 3574.6606334842 0.0) (10 5961.6440928131 3584.6310683305 0.0) (10 5972.0591232202
3527.5646814152 0.0) (10 5946.4557692308 3536.9535067873 0.0))
((0 . "LWPOLYLINE") (100 . "AcDbEntity") (8 . "PLANTS") (62 . 94) (370 . 13) (100 . "AcDbPolyline") (90 . 2) (70 . 0)
(43 . 0.0) (10 5938.9140271493 3574.6606334842) (10 5957.7679864253 3608.5972850679))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5938.9140271493 916.2895927602 0.0) (10 5946.1302287097 896.5130343863 0.0) (10 5981.155614045
893.6744123892 0.0) (10 5991.704638009 912.5197963801 0.0))
((0 . "LWPOLYLINE") (100 . "AcDbEntity") (8 . "PLANTS") (62 . 94) (370 . 13) (100 . "AcDbPolyline") (90 . 2) (70 . 0)
(43 . 0.0) (10 5942.6845022624 927.6018099548) (10 5938.9140271493 916.2895927602))
((0 . "LWPOLYLINE") (100 . "AcDbEntity") (8 . "PLANTS") (62 . 94) (370 . 13) (100 . "AcDbPolyline") (90 . 3) (70 . 0)
(43 . 0.0) (10 6055.8066742081 516.5921945701) (10 5950.2262443439 516.5852941176) (10 5938.9140271493 512.8195701357))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5942.6845022624 4030.9204751131 0.0) (10 5933.7867379262 4032.9778580566 0.0) (10 5918.1494122156
4044.0390725531 0.0) (10 5920.4337667309 4055.9563121222 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5948.7003296695 4067.2629372977 0.0) (10 5978.6405385285 4054.2617975726 0.0) (10 5953.6503257445
3992.3657378177 0.0) (10 5999.2455882353 3989.4415158371 0.0))
((0 . "LWPOLYLINE") (100 . "AcDbEntity") (8 . "PLANTS") (62 . 94) (370 . 13) (100 . "AcDbPolyline") (90 . 2) (70 . 0)
(43 . 0.0) (10 5980.3924208145 3755.6561085973) (10 5942.6845022624 3774.5093891403))
((0 . "LWPOLYLINE") (100 . "AcDbEntity") (8 . "PLANTS") (62 . 94) (370 . 13) (100 . "AcDbPolyline") (90 . 2) (70 . 0)
(43 . 0.0) (10 5957.7679864253 3819.7582579186) (10 5942.6845022624 3774.5093891403))
((0 . "LWPOLYLINE") (100 . "AcDbEntity") (8 . "PLANTS") (62 . 94) (370 . 13) (100 . "AcDbPolyline") (90 . 2) (70 . 0)
(43 . 0.0) (10 5942.6845022624 927.6018099548) (10 5976.6211538462 935.1442307692))
((0 . "LWPOLYLINE") (100 . "AcDbEntity") (8 . "PLANTS") (62 . 94) (370 . 13) (100 . "AcDbPolyline") (90 . 2) (70 . 0)
(43 . 0.0) (10 5946.4557692308 3959.2760180995) (10 5965.3089366516 3966.817081448))
((0 . "LWPOLYLINE") (100 . "AcDbEntity") (8 . "PLANTS") (62 . 94) (370 . 13) (100 . "AcDbPolyline") (90 . 2) (70 . 0)
(43 . 0.0) (10 5965.3089366516 3714.1783936652) (10 5946.4557692308 3714.1783936652))
((0 . "LWPOLYLINE") (100 . "AcDbEntity") (8 . "PLANTS") (62 . 94) (370 . 13) (100 . "AcDbPolyline") (90 . 3) (70 . 0)
(43 . 0.0) (10 5950.2262443439 365.7607466063) (10 5953.8489819005 392.1578054299) (10 5946.4557692308 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5950.2262443439 3895.1738687783 0.0) (10 5967.5215852195 3904.1511611453 0.0) (10 5982.7514359084
3878.6289236745 0.0) (10 5999.2455882353 3891.4027149321 0.0))
((0 . "LWPOLYLINE") (100 . "AcDbEntity") (8 . "PLANTS") (62 . 94) (370 . 13) (100 . "AcDbPolyline") (90 . 2) (70 . 0)
(43 . 0.0) (10 5961.5384615385 3431.3722850679) (10 5950.2262443439 3442.6845022624))
((0 . "LWPOLYLINE") (100 . "AcDbEntity") (8 . "PLANTS") (62 . 94) (370 . 13) (100 . "AcDbPolyline") (90 . 3) (70 . 0)
(43 . 0.0) (10 5950.2262443439 365.7607466063) (10 5965.4574660633 343.2847285068) (10 5987.9333710407 331.8240950226))
((0 . "LWPOLYLINE") (100 . "AcDbEntity") (8 . "PLANTS") (62 . 94) (370 . 13) (100 . "AcDbPolyline") (90 . 3) (70 . 0)
(43 . 0.0) (10 5995.4751131222 3657.6173076923) (10 5980.2438914027 3619.9157239819) (10 5957.7679864253
3608.5972850679))
((0 . "LWPOLYLINE") (100 . "AcDbEntity") (8 . "PLANTS") (62 . 94) (370 . 13) (100 . "AcDbPolyline") (90 . 3) (70 . 0)
(43 . 0.0) (10 5961.5384615385 1108.5972850679) (10 5961.686199095 1085.9797511312) (10 5965.3089366516
1078.4304298643))
((0 . "LWPOLYLINE") (100 . "AcDbEntity") (8 . "PLANTS") (62 . 94) (370 . 13) (100 . "AcDbPolyline") (90 . 3) (70 . 0)
(43 . 0.0) (10 5965.3089366516 3714.1783936652) (10 5966.5069004525 3702.8654977376) (10 5995.4751131222
3657.6173076923))
((0 . "LWPOLYLINE") (100 . "AcDbEntity") (8 . "PLANTS") (62 . 94) (370 . 13) (100 . "AcDbPolyline") (90 . 2) (70 . 0)
(43 . 0.0) (10 5965.3089366516 3714.1783936652) (10 5980.3924208145 3729.260520362))
((0 . "LWPOLYLINE") (100 . "AcDbEntity") (8 . "PLANTS") (62 . 94) (370 . 13) (100 . "AcDbPolyline") (90 . 2) (70 . 0)
(43 . 0.0) (10 5969.0802036199 294.1176470588) (10 5969.0802036199 267.7234162896))
((0 . "LWPOLYLINE") (100 . "AcDbEntity") (8 . "PLANTS") (62 . 94) (370 . 13) (100 . "AcDbPolyline") (90 . 2) (70 . 0)
(43 . 0.0) (10 5969.0802036199 294.1176470588) (10 5991.7046380091 301.6600678733))
((0 . "LWPOLYLINE") (100 . "AcDbEntity") (8 . "PLANTS") (62 . 94) (370 . 13) (100 . "AcDbPolyline") (90 . 2) (70 . 0)
(43 . 0.0) (10 5969.0802036199 267.7234162896) (10 5972.850678733 241.3263574661))
((0 . "LWPOLYLINE") (100 . "AcDbEntity") (8 . "PLANTS") (62 . 94) (370 . 13) (100 . "AcDbPolyline") (90 . 2) (70 . 0)
(43 . 0.0) (10 5972.850678733 241.3263574661) (10 6036.9535067873 241.3263574661))
((0 . "LWPOLYLINE") (100 . "AcDbEntity") (8 . "PLANTS") (62 . 94) (370 . 13) (100 . "AcDbPolyline") (90 . 2) (70 . 0)
(43 . 0.0) (10 5976.6211538462 935.1442307692) (10 5991.7046380091 912.5197963801))
((0 . "LWPOLYLINE") (100 . "AcDbEntity") (8 . "PLANTS") (62 . 94) (370 . 13) (100 . "AcDbPolyline") (90 . 2) (70 . 0)
(43 . 0.0) (10 5978.5067873303 980.3930995475) (10 5976.6211538462 935.1442307692))
((0 . "LWPOLYLINE") (100 . "AcDbEntity") (8 . "PLANTS") (62 . 94) (370 . 13) (100 . "AcDbPolyline") (90 . 2) (70 . 0)
(43 . 0.0) (10 5978.5067873303 980.3930995475) (10 6006.7873303167 980.3930995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 5991.7046380091 1033.181561086 0.0) (10 5971.0156720953 1027.9067528902 0.0) (10 5974.7013984652
992.2104537688 0.0) (10 5978.5067873303 980.3930995475 0.0))
((0 . "LWPOLYLINE") (100 . "AcDbEntity") (8 . "PLANTS") (62 . 94) (370 . 13) (100 . "AcDbPolyline") (90 . 2) (70 . 0)
(43 . 0.0) (10 5980.3924208145 3755.6561085973) (10 5980.3924208145 3729.260520362))
((0 . "LWPOLYLINE") (100 . "AcDbEntity") (8 . "PLANTS") (62 . 94) (370 . 13) (100 . "AcDbPolyline") (90 . 2) (70 . 0)
(43 . 0.0) (10 5980.3924208145 3755.6561085973) (10 6010.5578054299 3770.739479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6048.2657239819 3706.6360859728 0.0) (10 6032.8248533428 3727.0398441176 0.0) (10 6002.6505337391
3726.9337487563 0.0) (10 5980.3924208145 3729.260520362 0.0))
((0 . "LWPOLYLINE") (100 . "AcDbEntity") (8 . "PLANTS") (62 . 94) (370 . 13) (100 . "AcDbPolyline") (90 . 2) (70 . 0)
(43 . 0.0) (10 5991.7046380091 309.1996606335) (10 5987.9333710407 331.8240950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6010.5578054299 392.1578054299 0.0) (10 5982.7955256057 379.1663299333 0.0) (10 6008.0848062653
345.9929165786 0.0) (10 5987.9333710407 331.8240950226 0.0))
((0 . "LWPOLYLINE") (100 . "AcDbEntity") (8 . "PLANTS") (62 . 94) (370 . 13) (100 . "AcDbPolyline") (90 . 2) (70 . 0)
(43 . 0.0) (10 5991.7046380091 1033.181561086) (10 6010.5578054299 1014.3297511312))
((0 . "LWPOLYLINE") (100 . "AcDbEntity") (8 . "PLANTS") (62 . 94) (370 . 13) (100 . "AcDbPolyline") (90 . 3) (70 . 0)
(43 . 0.0) (10 5991.7046380091 1033.181561086) (10 5996.6722850679 1052.0292986425) (10 6003.0168552036
1059.5786199095))
((0 . "LWPOLYLINE") (100 . "AcDbEntity") (8 . "PLANTS") (62 . 94) (370 . 13) (100 . "AcDbPolyline") (90 . 2) (70 . 0)
(43 . 0.0) (10 6029.4117647059 912.5197963801) (10 5991.7046380091 912.5197963801))
((0 . "LWPOLYLINE") (100 . "AcDbEntity") (8 . "PLANTS") (62 . 94) (370 . 13) (100 . "AcDbPolyline") (90 . 2) (70 . 0)
(43 . 0.0) (10 5991.7046380091 309.1996606335) (10 5991.7046380091 301.6600678733))
((0 . "LWPOLYLINE") (100 . "AcDbEntity") (8 . "PLANTS") (62 . 94) (370 . 13) (100 . "AcDbPolyline") (90 . 3) (70 . 0)
(43 . 0.0) (10 5991.7046380091 309.1996606335) (10 6014.3290723982 320.3641402715) (10 6040.7239819005 320.5118778281))
((0 . "LWPOLYLINE") (100 . "AcDbEntity") (8 . "PLANTS") (62 . 94) (370 . 13) (100 . "AcDbPolyline") (90 . 2) (70 . 0)
(43 . 0.0) (10 6021.8700226244 282.8054298643) (10 5991.7046380091 301.6600678733))
((0 . "LWPOLYLINE") (100 . "AcDbEntity") (8 . "PLANTS") (62 . 94) (370 . 13) (100 . "AcDbPolyline") (90 . 2) (70 . 0)
(43 . 0.0) (10 5995.4751131222 3657.6173076923) (10 6018.0995475113 3657.6173076923))
((0 . "LWPOLYLINE") (100 . "AcDbEntity") (8 . "PLANTS") (62 . 94) (370 . 13) (100 . "AcDbPolyline") (90 . 2) (70 . 0)
(43 . 0.0) (10 5999.2455882353 3891.4027149321) (10 5999.2455882353 3902.7149321267))
((0 . "LWPOLYLINE") (100 . "AcDbEntity") (8 . "PLANTS") (62 . 94) (370 . 13) (100 . "AcDbPolyline") (90 . 2) (70 . 0)
(43 . 0.0) (10 5999.2455882353 3891.4027149321) (10 6036.9535067873 3865.0071266968))
((0 . "LWPOLYLINE") (100 . "AcDbEntity") (8 . "PLANTS") (62 . 94) (370 . 13) (100 . "AcDbPolyline") (90 . 2) (70 . 0)
(43 . 0.0) (10 6006.7873303167 980.3930995475) (10 6033.182239819 969.0808823529))
((0 . "LWPOLYLINE") (100 . "AcDbEntity") (8 . "PLANTS") (62 . 94) (370 . 13) (100 . "AcDbPolyline") (90 . 2) (70 . 0)
(43 . 0.0) (10 6006.7873303167 980.3930995475) (10 6010.5578054299 1014.3297511312))
((0 . "LWPOLYLINE") (100 . "AcDbEntity") (8 . "PLANTS") (62 . 94) (370 . 13) (100 . "AcDbPolyline") (90 . 3) (70 . 0)
(43 . 0.0) (10 6010.5578054299 3770.739479638) (10 6029.4117647059 3763.3455882353) (10 6059.5779411765
3759.4272624434))
((0 . "LWPOLYLINE") (100 . "AcDbEntity") (8 . "PLANTS") (62 . 94) (370 . 13) (100 . "AcDbPolyline") (90 . 3) (70 . 0)
(43 . 0.0) (10 6010.5578054299 3770.739479638) (10 6010.7055429864 3808.446040724) (10 6018.0995475113 3838.6127828054))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4044420453) (40
. 1) (40 . 1) (40 . 1) (40 . 1) (10 6093.5145927602 1048.2664027149 0.0) (10 6083.297472087 1062.1739294626 0.0) (10
6038.6183656157 1076.02190489 0.0) (10 6033.6519236059 1011.4416735078 0.0) (10 6010.5578054299 1014.3297511311 0.0))
((0 . "LWPOLYLINE") (100 . "AcDbEntity") (8 . "PLANTS") (62 . 94) (370 . 13) (100 . "AcDbPolyline") (90 . 3) (70 . 0)
(43 . 0.0) (10 6036.9535067873 3849.925) (10 6025.6475113122 3839.8166289593) (10 6018.0995475113 3838.6127828054))
((0 . "LWPOLYLINE") (100 . "AcDbEntity") (8 . "PLANTS") (62 . 94) (370 . 13) (100 . "AcDbPolyline") (90 . 2) (70 . 0)
(43 . 0.0) (10 6025.6412895928 3646.3050904977) (10 6018.0995475113 3657.6173076923))
((0 . "LWPOLYLINE") (100 . "AcDbEntity") (8 . "PLANTS") (62 . 94) (370 . 13) (100 . "AcDbPolyline") (90 . 3) (70 . 0)
(43 . 0.0) (10 6018.0995475113 3657.6173076923) (10 6044.3398190045 3684.1600678733) (10 6048.2657239819
3695.3238687783))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7318586349) (40
. 1) (40 . 1) (40 . 1) (40 . 1) (10 6063.3484162896 3985.6716063348 0.0) (10 6067.2114291523 4012.7269587059 0.0) (10
6044.740904903 4107.3824329709 0.0) (10 6008.4808669856 4050.1236092363 0.0) (10 6021.8700226244 4038.4615384615 0.0))
((0 . "LWPOLYLINE") (100 . "AcDbEntity") (8 . "PLANTS") (62 . 94) (370 . 13) (100 . "AcDbPolyline") (90 . 2) (70 . 0)
(43 . 0.0) (10 6044.4944570136 3936.6515837104) (10 6025.6412895928 3921.5682126697))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6044.4944570136 3597.2850678733 0.0) (10 6022.9212025341 3595.5211362223 0.0) (10 6016.4227487362
3634.9380266645 0.0) (10 6025.6412895928 3646.3050904977 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.701835776) (40 .
1) (40 . 1) (40 . 1) (40 . 1) (10 6025.6412895928 3646.3050904977 0.0) (10 6049.3125459943 3645.1313785376 0.0) (10
6084.8976493643 3649.7758493434 0.0) (10 6116.5862214812 3660.6912719499 0.0) (10 6123.6799773756 3668.9295248868 0.0))
((0 . "LWPOLYLINE") (100 . "AcDbEntity") (8 . "PLANTS") (62 . 94) (370 . 13) (100 . "AcDbPolyline") (90 . 3) (70 . 0)
(43 . 0.0) (10 6044.4944570136 935.1442307692) (10 6040.7239819005 931.3716063348) (10 6029.4117647059 931.3716063348))
((0 . "LWPOLYLINE") (100 . "AcDbEntity") (8 . "PLANTS") (62 . 94) (370 . 13) (100 . "AcDbPolyline") (90 . 2) (70 . 0)
(43 . 0.0) (10 6029.4117647059 931.3716063348) (10 6029.4117647059 912.5197963801))
((0 . "LWPOLYLINE") (100 . "AcDbEntity") (8 . "PLANTS") (62 . 94) (370 . 13) (100 . "AcDbPolyline") (90 . 2) (70 . 0)
(43 . 0.0) (10 6029.4117647059 931.3716063348) (10 6033.182239819 969.0808823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6029.4117647059 912.5197963801 0.0) (10 6041.3214295096 899.9342956624 0.0) (10 6063.5485626227
895.0674109627 0.0) (10 6078.4311085973 904.9773755656 0.0))
((0 . "LWPOLYLINE") (100 . "AcDbEntity") (8 . "PLANTS") (62 . 94) (370 . 13) (100 . "AcDbPolyline") (90 . 2) (70 . 0)
(43 . 0.0) (10 6033.182239819 969.0808823529) (10 6052.036199095 969.0808823529))
((0 . "LWPOLYLINE") (100 . "AcDbEntity") (8 . "PLANTS") (62 . 94) (370 . 13) (100 . "AcDbPolyline") (90 . 2) (70 . 0)
(43 . 0.0) (10 6036.9535067873 3849.925) (10 6036.9535067873 3865.0071266968))
((0 . "LWPOLYLINE") (100 . "AcDbEntity") (8 . "PLANTS") (62 . 94) (370 . 13) (100 . "AcDbPolyline") (90 . 3) (70 . 0)
(43 . 0.0) (10 6067.1188914027 3917.7983031674) (10 6062.292081448 3902.7149321267) (10 6036.9535067873
3865.0071266968))
((0 . "LWPOLYLINE") (100 . "AcDbEntity") (8 . "PLANTS") (62 . 94) (370 . 13) (100 . "AcDbPolyline") (90 . 3) (70 . 0)
(43 . 0.0) (10 6127.4512443439 3876.3193438914) (10 6085.9728506787 3858.5227375566) (10 6036.9535067873 3849.925))
((0 . "LWPOLYLINE") (100 . "AcDbEntity") (8 . "PLANTS") (62 . 94) (370 . 13) (100 . "AcDbPolyline") (90 . 2) (70 . 0)
(43 . 0.0) (10 6063.3484162896 411.0096153846) (10 6036.9535067873 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6123.6799773756 237.556561086 0.0) (10 6097.7803804482 223.7597965913 0.0) (10 6060.2698127182
221.669159467 0.0) (10 6036.9535067873 241.3263574661 0.0))
((0 . "LWPOLYLINE") (100 . "AcDbEntity") (8 . "PLANTS") (62 . 94) (370 . 13) (100 . "AcDbPolyline") (90 . 2) (70 . 0)
(43 . 0.0) (10 6048.2657239819 279.0356334842) (10 6036.9535067873 241.3263574661))
((0 . "LWPOLYLINE") (100 . "AcDbEntity") (8 . "PLANTS") (62 . 94) (370 . 13) (100 . "AcDbPolyline") (90 . 3) (70 . 0)
(43 . 0.0) (10 6040.7239819005 320.5118778281) (10 6040.87239819 297.8874434389) (10 6048.2657239819 279.0356334842))
((0 . "LWPOLYLINE") (100 . "AcDbEntity") (8 . "PLANTS") (62 . 94) (370 . 13) (100 . "AcDbPolyline") (90 . 2) (70 . 0)
(43 . 0.0) (10 6040.7239819005 320.5118778281) (10 6097.2850678733 328.0542986425))
((0 . "LWPOLYLINE") (100 . "AcDbEntity") (8 . "PLANTS") (62 . 94) (370 . 13) (100 . "AcDbPolyline") (90 . 2) (70 . 0)
(43 . 0.0) (10 6067.1188914027 3917.7983031674) (10 6044.4944570136 3936.6515837104))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6063.3484162896 3985.6716063348 0.0) (10 6039.7121361467 3988.423263757 0.0) (10 6012.1456659096
3953.5780515646 0.0) (10 6044.4944570136 3936.6515837104 0.0))
((0 . "LWPOLYLINE") (100 . "AcDbEntity") (8 . "PLANTS") (62 . 94) (370 . 13) (100 . "AcDbPolyline") (90 . 2) (70 . 0)
(43 . 0.0) (10 6044.4944570136 3597.2850678733) (10 6044.4944570136 3589.7433257919))
((0 . "LWPOLYLINE") (100 . "AcDbEntity") (8 . "PLANTS") (62 . 94) (370 . 13) (100 . "AcDbPolyline") (90 . 2) (70 . 0)
(43 . 0.0) (10 6044.4944570136 3597.2850678733) (10 6070.890158371 3601.0555429864))
((0 . "LWPOLYLINE") (100 . "AcDbEntity") (8 . "PLANTS") (62 . 94) (370 . 13) (100 . "AcDbPolyline") (90 . 2) (70 . 0)
(43 . 0.0) (10 6048.2657239819 3706.6360859729) (10 6048.2657239819 3695.3238687783))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6048.2657239819 3706.6360859729 0.0) (10 6063.4751441533 3718.9802941386 0.0) (10 6058.7506886814
3743.0471790348 0.0) (10 6059.5779411765 3759.4272624434 0.0))
((0 . "LWPOLYLINE") (100 . "AcDbEntity") (8 . "PLANTS") (62 . 94) (370 . 13) (100 . "AcDbPolyline") (90 . 2) (70 . 0)
(43 . 0.0) (10 6104.8268099548 3695.3238687783) (10 6048.2657239819 3695.3238687783))
((0 . "LWPOLYLINE") (100 . "AcDbEntity") (8 . "PLANTS") (62 . 94) (370 . 13) (100 . "AcDbPolyline") (90 . 3) (70 . 0)
(43 . 0.0) (10 6123.6799773756 252.6385746606) (10 6089.7433257919 270.4437782805) (10 6048.2657239819 279.0356334842))
((0 . "LWPOLYLINE") (100 . "AcDbEntity") (8 . "PLANTS") (62 . 94) (370 . 13) (100 . "AcDbPolyline") (90 . 3) (70 . 0)
(43 . 0.0) (10 6082.2023755656 938.9140271493) (10 6070.8832579186 957.7610859729) (10 6052.036199095 969.0808823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6093.5145927602 1003.0175339367 0.0) (10 6074.1117527796 1016.1341573709 0.0) (10 6047.7730772409
989.3163329109 0.0) (10 6052.036199095 969.0808823529 0.0))
((0 . "LWPOLYLINE") (100 . "AcDbEntity") (8 . "PLANTS") (62 . 94) (370 . 13) (100 . "AcDbPolyline") (90 . 3) (70 . 0)
(43 . 0.0) (10 6067.1188914027 426.0944570136) (10 6065.9148190045 433.6416289593) (10 6052.036199095 448.7188914027))
((0 . "LWPOLYLINE") (100 . "AcDbEntity") (8 . "PLANTS") (62 . 94) (370 . 13) (100 . "AcDbPolyline") (90 . 3) (70 . 0)
(43 . 0.0) (10 6062.756313685 4112.8853309039) (10 6083.4002262443 4057.4632352941) (10 6108.5972850679
4042.2326923077))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.2146182278) (40
. 1) (40 . 1) (40 . 1) (40 . 1) (10 6157.6166289593 3819.7582579186 0.0) (10 6149.280143296 3822.3537205818 0.0) (10
6116.0055868898 3804.5920932232 0.0) (10 6070.2253452263 3797.3611826857 0.0) (10 6059.5779411765 3759.4272624434 0.0))
((0 . "LWPOLYLINE") (100 . "AcDbEntity") (8 . "PLANTS") (62 . 94) (370 . 13) (100 . "AcDbPolyline") (90 . 2) (70 . 0)
(43 . 0.0) (10 6102.9411764706 3964.9321266968) (10 6063.3484162896 3985.6716063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6063.3484162896 411.0096153846 0.0) (10 6060.3733957232 392.8810876509 0.0) (10 6077.3615408085
378.715443862 0.0) (10 6093.5145927602 380.8455882353 0.0))
((0 . "LWPOLYLINE") (100 . "AcDbEntity") (8 . "PLANTS") (62 . 94) (370 . 13) (100 . "AcDbPolyline") (90 . 2) (70 . 0)
(43 . 0.0) (10 6067.1188914027 426.0944570136) (10 6063.3484162896 411.0096153846))
((0 . "LWPOLYLINE") (100 . "AcDbEntity") (8 . "PLANTS") (62 . 94) (370 . 13) (100 . "AcDbPolyline") (90 . 3) (70 . 0)
(43 . 0.0) (10 6101.0555429864 3929.110520362) (10 6082.2023755656 3918.8544117647) (10 6067.1188914027
3917.7983031674))
((0 . "LWPOLYLINE") (100 . "AcDbEntity") (8 . "PLANTS") (62 . 94) (370 . 13) (100 . "AcDbPolyline") (90 . 2) (70 . 0)
(43 . 0.0) (10 6067.1188914027 3612.367760181) (10 6070.890158371 3601.0555429864))
((0 . "LWPOLYLINE") (100 . "AcDbEntity") (8 . "PLANTS") (62 . 94) (370 . 13) (100 . "AcDbPolyline") (90 . 2) (70 . 0)
(43 . 0.0) (10 6067.1188914027 426.0944570136) (10 6082.2023755656 426.0944570136))
((0 . "LWPOLYLINE") (100 . "AcDbEntity") (8 . "PLANTS") (62 . 94) (370 . 13) (100 . "AcDbPolyline") (90 . 3) (70 . 0)
(43 . 0.0) (10 6085.9728506787 3578.4311085973) (10 6081.1459276018 3593.5076923077) (10 6070.890158371
3601.0555429864))
((0 . "LWPOLYLINE") (100 . "AcDbEntity") (8 . "PLANTS") (62 . 94) (370 . 13) (100 . "AcDbPolyline") (90 . 2) (70 . 0)
(43 . 0.0) (10 6108.6034135555 4146.2304525678) (10 6108.5972850679 4042.2326923077))
((0 . "LWPOLYLINE") (100 . "AcDbEntity") (8 . "PLANTS") (62 . 94) (370 . 13) (100 . "AcDbPolyline") (90 . 2) (70 . 0)
(43 . 0.0) (10 6078.4311085973 904.9773755656) (10 6082.2023755656 938.9140271493))
((0 . "LWPOLYLINE") (100 . "AcDbEntity") (8 . "PLANTS") (62 . 94) (370 . 13) (100 . "AcDbPolyline") (90 . 3) (70 . 0)
(43 . 0.0) (10 6078.4311085973 904.9773755656) (10 6112.367760181 905.1320135747) (10 6127.4512443439 916.2895927602))
((0 . "LWPOLYLINE") (100 . "AcDbEntity") (8 . "PLANTS") (62 . 94) (370 . 13) (100 . "AcDbPolyline") (90 . 2) (70 . 0)
(43 . 0.0) (10 6123.6799773756 938.9140271493) (10 6082.2023755656 938.9140271493))
((0 . "LWPOLYLINE") (100 . "AcDbEntity") (8 . "PLANTS") (62 . 94) (370 . 13) (100 . "AcDbPolyline") (90 . 2) (70 . 0)
(43 . 0.0) (10 6082.2023755656 426.0944570136) (10 6093.5145927602 388.3851809955))
((0 . "LWPOLYLINE") (100 . "AcDbEntity") (8 . "PLANTS") (62 . 94) (370 . 13) (100 . "AcDbPolyline") (90 . 3) (70 . 0)
(43 . 0.0) (10 6082.2023755656 426.0944570136) (10 6096.2287330317 448.7188914027) (10 6101.0555429864 471.3433257919))
((0 . "LWPOLYLINE") (100 . "AcDbEntity") (8 . "PLANTS") (62 . 94) (370 . 13) (100 . "AcDbPolyline") (90 . 2) (70 . 0)
(43 . 0.0) (10 6093.5145927602 380.8455882353) (10 6093.5145927602 388.3851809955))
((0 . "LWPOLYLINE") (100 . "AcDbEntity") (8 . "PLANTS") (62 . 94) (370 . 13) (100 . "AcDbPolyline") (90 . 3) (70 . 0)
(43 . 0.0) (10 6131.221719457 411.0096153846) (10 6120.5971719457 391.4763574661) (10 6093.5145927602 388.3851809955))
((0 . "LWPOLYLINE") (100 . "AcDbEntity") (8 . "PLANTS") (62 . 94) (370 . 13) (100 . "AcDbPolyline") (90 . 3) (70 . 0)
(43 . 0.0) (10 6093.5145927602 380.8455882353) (10 6097.4397058824 354.4485294118) (10 6104.8268099548 339.3665158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6123.6799773756 252.6385746606 0.0) (10 6150.3489636105 280.7526936448 0.0) (10 6095.9465142026
299.93478112 0.0) (10 6097.2850678733 328.0542986425 0.0))
((0 . "LWPOLYLINE") (100 . "AcDbEntity") (8 . "PLANTS") (62 . 94) (370 . 13) (100 . "AcDbPolyline") (90 . 2) (70 . 0)
(43 . 0.0) (10 6104.8268099548 339.3665158371) (10 6097.2850678733 328.0542986425))
((0 . "LWPOLYLINE") (100 . "AcDbEntity") (8 . "PLANTS") (62 . 94) (370 . 13) (100 . "AcDbPolyline") (90 . 2) (70 . 0)
(43 . 0.0) (10 6119.9095022624 3921.5682126697) (10 6101.0555429864 3929.110520362))
((0 . "LWPOLYLINE") (100 . "AcDbEntity") (8 . "PLANTS") (62 . 94) (370 . 13) (100 . "AcDbPolyline") (90 . 2) (70 . 0)
(43 . 0.0) (10 6101.0555429864 3929.110520362) (10 6102.9411764706 3964.9321266968))
((0 . "LWPOLYLINE") (100 . "AcDbEntity") (8 . "PLANTS") (62 . 94) (370 . 13) (100 . "AcDbPolyline") (90 . 2) (70 . 0)
(43 . 0.0) (10 6101.0555429864 3431.3722850679) (10 6112.367760181 3446.4557692308))
((0 . "LWPOLYLINE") (100 . "AcDbEntity") (8 . "PLANTS") (62 . 94) (370 . 13) (100 . "AcDbPolyline") (90 . 2) (70 . 0)
(43 . 0.0) (10 6101.0555429864 516.5921945701) (10 6119.9095022624 520.3619909502))
((0 . "LWPOLYLINE") (100 . "AcDbEntity") (8 . "PLANTS") (62 . 94) (370 . 13) (100 . "AcDbPolyline") (90 . 3) (70 . 0)
(43 . 0.0) (10 6102.9411764706 3964.9321266968) (10 6108.4495475113 3981.9004524887) (10 6108.5972850679
4012.0659502262))
((0 . "LWPOLYLINE") (100 . "AcDbEntity") (8 . "PLANTS") (62 . 94) (370 . 13) (100 . "AcDbPolyline") (90 . 2) (70 . 0)
(43 . 0.0) (10 6157.6168552036 3966.817081448) (10 6102.9411764706 3964.9321266968))
((0 . "LWPOLYLINE") (100 . "AcDbEntity") (8 . "PLANTS") (62 . 94) (370 . 13) (100 . "AcDbPolyline") (90 . 2) (70 . 0)
(43 . 0.0) (10 6119.9095022624 3687.7828054299) (10 6104.8268099548 3695.3238687783))
((0 . "LWPOLYLINE") (100 . "AcDbEntity") (8 . "PLANTS") (62 . 94) (370 . 13) (100 . "AcDbPolyline") (90 . 3) (70 . 0)
(43 . 0.0) (10 6127.4512443439 3763.1971719457) (10 6109.6536199095 3733.0316742081) (10 6104.8268099548
3695.3238687783))
((0 . "LWPOLYLINE") (100 . "AcDbEntity") (8 . "PLANTS") (62 . 94) (370 . 13) (100 . "AcDbPolyline") (90 . 2) (70 . 0)
(43 . 0.0) (10 6116.1390271493 339.3665158371) (10 6104.8268099548 339.3665158371))
((0 . "LWPOLYLINE") (100 . "AcDbEntity") (8 . "PLANTS") (62 . 94) (370 . 13) (100 . "AcDbPolyline") (90 . 2) (70 . 0)
(43 . 0.0) (10 6108.5972850679 4012.0659502262) (10 6108.5972850679 4042.2326923077))
((0 . "LWPOLYLINE") (100 . "AcDbEntity") (8 . "PLANTS") (62 . 94) (370 . 13) (100 . "AcDbPolyline") (90 . 2) (70 . 0)
(43 . 0.0) (10 6157.6168552036 4012.0659502262) (10 6108.5972850679 4012.0659502262))
((0 . "LWPOLYLINE") (100 . "AcDbEntity") (8 . "PLANTS") (62 . 94) (370 . 13) (100 . "AcDbPolyline") (90 . 2) (70 . 0)
(43 . 0.0) (10 6112.367760181 3446.4557692308) (10 6116.1390271493 3469.0802036199))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6112.367760181 3446.4557692308 0.0) (10 6127.2787729959 3445.6398359125 0.0) (10 6154.0129431159
3456.9132139981 0.0) (10 6150.075678733 3476.6211538462 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6165.1583710408 237.556561086 0.0) (10 6174.0263997361 277.1254537094 0.0) (10 6141.8942559981
312.9555652995 0.0) (10 6116.1390271493 339.3665158371 0.0))
((0 . "LWPOLYLINE") (100 . "AcDbEntity") (8 . "PLANTS") (62 . 94) (370 . 13) (100 . "AcDbPolyline") (90 . 3) (70 . 0)
(43 . 0.0) (10 6116.1390271493 339.3665158371) (10 6123.6868778281 345.7102941176) (10 6161.3878959276 354.4485294118))
((0 . "LWPOLYLINE") (100 . "AcDbEntity") (8 . "PLANTS") (62 . 94) (370 . 13) (100 . "AcDbPolyline") (90 . 2) (70 . 0)
(43 . 0.0) (10 6127.4512443439 3876.3193438914) (10 6119.9095022624 3921.5682126697))
((0 . "LWPOLYLINE") (100 . "AcDbEntity") (8 . "PLANTS") (62 . 94) (370 . 13) (100 . "AcDbPolyline") (90 . 2) (70 . 0)
(43 . 0.0) (10 6119.9095022624 3921.5682126697) (10 6161.3878959276 3929.110520362))
((0 . "LWPOLYLINE") (100 . "AcDbEntity") (8 . "PLANTS") (62 . 94) (370 . 13) (100 . "AcDbPolyline") (90 . 2) (70 . 0)
(43 . 0.0) (10 6119.9095022624 3687.7828054299) (10 6123.6799773756 3668.9295248869))
((0 . "LWPOLYLINE") (100 . "AcDbEntity") (8 . "PLANTS") (62 . 94) (370 . 13) (100 . "AcDbPolyline") (90 . 3) (70 . 0)
(43 . 0.0) (10 6142.5339366516 3733.0316742081) (10 6141.3359728507 3714.1783936652) (10 6119.9095022624
3687.7828054299))
((0 . "LWPOLYLINE") (100 . "AcDbEntity") (8 . "PLANTS") (62 . 94) (370 . 13) (100 . "AcDbPolyline") (90 . 2) (70 . 0)
(43 . 0.0) (10 6123.6799773756 938.9140271493) (10 6119.9095022624 991.7053167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6119.9095022624 991.7053167421 0.0) (10 6105.7765911605 1028.0023735913 0.0) (10 6158.2698493285
1040.8979784115 0.0) (10 6134.9921945701 1078.4304298643 0.0))
((0 . "LWPOLYLINE") (100 . "AcDbEntity") (8 . "PLANTS") (62 . 94) (370 . 13) (100 . "AcDbPolyline") (90 . 2) (70 . 0)
(43 . 0.0) (10 6180.2410633484 995.4751131222) (10 6119.9095022624 991.7053167421))
((0 . "LWPOLYLINE") (100 . "AcDbEntity") (8 . "PLANTS") (62 . 94) (370 . 13) (100 . "AcDbPolyline") (90 . 2) (70 . 0)
(43 . 0.0) (10 6123.6799773756 3668.9295248869) (10 6138.7634615385 3668.9295248869))
((0 . "LWPOLYLINE") (100 . "AcDbEntity") (8 . "PLANTS") (62 . 94) (370 . 13) (100 . "AcDbPolyline") (90 . 2) (70 . 0)
(43 . 0.0) (10 6123.6799773756 938.9140271493) (10 6127.4512443439 916.2895927602))
((0 . "LWPOLYLINE") (100 . "AcDbEntity") (8 . "PLANTS") (62 . 94) (370 . 13) (100 . "AcDbPolyline") (90 . 2) (70 . 0)
(43 . 0.0) (10 6123.6799773756 252.6385746606) (10 6123.6799773756 237.556561086))
((0 . "LWPOLYLINE") (100 . "AcDbEntity") (8 . "PLANTS") (62 . 94) (370 . 13) (100 . "AcDbPolyline") (90 . 2) (70 . 0)
(43 . 0.0) (10 6165.1583710407 237.556561086) (10 6123.6799773756 237.556561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6127.4512443439 3876.3193438914 0.0) (10 6158.2622782977 3881.1099772621 0.0) (10 6168.2434491443
3841.1592193116 0.0) (10 6199.0950226244 3846.1538461538 0.0))
((0 . "LWPOLYLINE") (100 . "AcDbEntity") (8 . "PLANTS") (62 . 94) (370 . 13) (100 . "AcDbPolyline") (90 . 2) (70 . 0)
(43 . 0.0) (10 6131.221719457 3352.1867647059) (10 6127.4512443439 3363.4989819005))
((0 . "LWPOLYLINE") (100 . "AcDbEntity") (8 . "PLANTS") (62 . 94) (370 . 13) (100 . "AcDbPolyline") (90 . 2) (70 . 0)
(43 . 0.0) (10 6131.221719457 3352.1867647059) (10 6127.4512443439 3340.8745475113))
((0 . "LWPOLYLINE") (100 . "AcDbEntity") (8 . "PLANTS") (62 . 94) (370 . 13) (100 . "AcDbPolyline") (90 . 3) (70 . 0)
(43 . 0.0) (10 6134.9921945701 1078.4304298643) (10 6123.8285067873 1101.0548642534) (10 6125.0175715815
1108.480717769))
((0 . "LWPOLYLINE") (100 . "AcDbEntity") (8 . "PLANTS") (62 . 94) (370 . 13) (100 . "AcDbPolyline") (90 . 2) (70 . 0)
(43 . 0.0) (10 6187.7828054299 916.2895927602) (10 6127.4512443439 916.2895927602))
((0 . "LWPOLYLINE") (100 . "AcDbEntity") (8 . "PLANTS") (62 . 94) (370 . 13) (100 . "AcDbPolyline") (90 . 2) (70 . 0)
(43 . 0.0) (10 6131.221719457 3352.1867647059) (10 6142.4731805582 3352.9748589617))
((0 . "LWPOLYLINE") (100 . "AcDbEntity") (8 . "PLANTS") (62 . 94) (370 . 13) (100 . "AcDbPolyline") (90 . 2) (70 . 0)
(43 . 0.0) (10 6131.221719457 418.5520361991) (10 6131.221719457 411.0096153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6131.221719457 411.0096153846 0.0) (10 6156.9865262583 413.2411168281 0.0) (10 6150.3530911248
358.1405440988 0.0) (10 6161.3878959276 354.4485294118 0.0))
((0 . "LWPOLYLINE") (100 . "AcDbEntity") (8 . "PLANTS") (62 . 94) (370 . 13) (100 . "AcDbPolyline") (90 . 2) (70 . 0)
(43 . 0.0) (10 6153.8461538462 1078.4304298643) (10 6134.9921945701 1078.4304298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6168.9288461538 3597.2850678733 0.0) (10 6130.0821093251 3579.8667317785 0.0) (10 6107.4906589362
3646.2745943537 0.0) (10 6138.7634615385 3668.9295248869 0.0))
((0 . "LWPOLYLINE") (100 . "AcDbEntity") (8 . "PLANTS") (62 . 94) (370 . 13) (100 . "AcDbPolyline") (90 . 2) (70 . 0)
(43 . 0.0) (10 6176.4705882353 3680.2417420814) (10 6138.7634615385 3668.9295248869))
((0 . "LWPOLYLINE") (100 . "AcDbEntity") (8 . "PLANTS") (62 . 94) (370 . 13) (100 . "AcDbPolyline") (90 . 3) (70 . 0)
(43 . 0.0) (10 6142.6283839665 1120.4880898497) (10 6152.6419683258 1112.2200226244) (10 6157.6166289593
1097.2850678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6150.0756787331 3476.6211538462 0.0) (10 6106.4462720749 3480.4827575287 0.0) (10 6132.6878371634
3574.6932919171 0.0) (10 6165.1583710408 3533.182239819 0.0))
((0 . "LWPOLYLINE") (100 . "AcDbEntity") (8 . "PLANTS") (62 . 94) (370 . 13) (100 . "AcDbPolyline") (90 . 2) (70 . 0)
(43 . 0.0) (10 6187.7828054299 3495.4751131222) (10 6150.075678733 3476.6211538462))
((0 . "LWPOLYLINE") (100 . "AcDbEntity") (8 . "PLANTS") (62 . 94) (370 . 13) (100 . "AcDbPolyline") (90 . 3) (70 . 0)
(43 . 0.0) (10 6153.8461538462 1078.4304298643) (10 6167.8725113122 1063.3421945701) (10 6176.4705882353
1040.7239819005))
((0 . "LWPOLYLINE") (100 . "AcDbEntity") (8 . "PLANTS") (62 . 94) (370 . 13) (100 . "AcDbPolyline") (90 . 2) (70 . 0)
(43 . 0.0) (10 6153.8461538462 1078.4304298643) (10 6157.6166289593 1097.2850678733))
((0 . "LWPOLYLINE") (100 . "AcDbEntity") (8 . "PLANTS") (62 . 94) (370 . 13) (100 . "AcDbPolyline") (90 . 2) (70 . 0)
(43 . 0.0) (10 6187.7828054299 1101.0548642534) (10 6157.6166289593 1097.2850678733))
((0 . "LWPOLYLINE") (100 . "AcDbEntity") (8 . "PLANTS") (62 . 94) (370 . 13) (100 . "AcDbPolyline") (90 . 2) (70 . 0)
(43 . 0.0) (10 6157.6168552036 4012.0659502262) (10 6157.6168552036 4027.149321267))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6229.261199095 4008.296040724 0.0) (10 6211.5416685827 4027.6799984765 0.0) (10 6182.4441191102
4035.9229897913 0.0) (10 6157.6168552036 4027.149321267 0.0))
((0 . "LWPOLYLINE") (100 . "AcDbEntity") (8 . "PLANTS") (62 . 94) (370 . 13) (100 . "AcDbPolyline") (90 . 3) (70 . 0)
(43 . 0.0) (10 6157.6168552036 3966.817081448) (10 6157.6168552036 4004.5186651584) (10 6157.6168552036
4012.0659502262))
((0 . "LWPOLYLINE") (100 . "AcDbEntity") (8 . "PLANTS") (62 . 94) (370 . 13) (100 . "AcDbPolyline") (90 . 2) (70 . 0)
(43 . 0.0) (10 6157.6168552036 3966.817081448) (10 6157.6168552036 3959.2760180995))
((0 . "LWPOLYLINE") (100 . "AcDbEntity") (8 . "PLANTS") (62 . 94) (370 . 13) (100 . "AcDbPolyline") (90 . 2) (70 . 0)
(43 . 0.0) (10 6161.3878959276 3929.110520362) (10 6157.6168552036 3959.2760180995))
((0 . "LWPOLYLINE") (100 . "AcDbEntity") (8 . "PLANTS") (62 . 94) (370 . 13) (100 . "AcDbPolyline") (90 . 3) (70 . 0)
(43 . 0.0) (10 6157.6168552036 3959.2760180995) (10 6195.3245475113 3971.7858597285) (10 6229.261199095 4008.296040724))
((0 . "LWPOLYLINE") (100 . "AcDbEntity") (8 . "PLANTS") (62 . 94) (370 . 13) (100 . "AcDbPolyline") (90 . 2) (70 . 0)
(43 . 0.0) (10 6161.3878959276 3929.110520362) (10 6161.3878959276 3921.5682126697))
((0 . "LWPOLYLINE") (100 . "AcDbEntity") (8 . "PLANTS") (62 . 94) (370 . 13) (100 . "AcDbPolyline") (90 . 2) (70 . 0)
(43 . 0.0) (10 6168.9288461538 961.5384615385) (10 6161.3878959276 957.7686651584))
((0 . "LWPOLYLINE") (100 . "AcDbEntity") (8 . "PLANTS") (62 . 94) (370 . 13) (100 . "AcDbPolyline") (90 . 2) (70 . 0)
(43 . 0.0) (10 6176.4705882353 350.6787330317) (10 6161.3878959276 354.4485294118))
((0 . "LWPOLYLINE") (100 . "AcDbEntity") (8 . "PLANTS") (62 . 94) (370 . 13) (100 . "AcDbPolyline") (90 . 3) (70 . 0)
(43 . 0.0) (10 6165.1583710407 237.556561086) (10 6187.7828054299 230.1625565611) (10 6225.4899321267 233.7867647059))
((0 . "LWPOLYLINE") (100 . "AcDbEntity") (8 . "PLANTS") (62 . 94) (370 . 13) (100 . "AcDbPolyline") (90 . 2) (70 . 0)
(43 . 0.0) (10 6180.2410633484 3785.8216063348) (10 6168.9288461538 3812.2171945701))
((0 . "LWPOLYLINE") (100 . "AcDbEntity") (8 . "PLANTS") (62 . 94) (370 . 13) (100 . "AcDbPolyline") (90 . 3) (70 . 0)
(43 . 0.0) (10 6168.9288461538 3597.2850678733) (10 6176.6252262443 3578.5857466063) (10 6187.7828054299
3574.6606334842))
((0 . "LWPOLYLINE") (100 . "AcDbEntity") (8 . "PLANTS") (62 . 94) (370 . 13) (100 . "AcDbPolyline") (90 . 3) (70 . 0)
(43 . 0.0) (10 6168.9288461538 3597.2850678733) (10 6180.3957013575 3623.6737556561) (10 6202.8654977376
3634.9928733032))
((0 . "LWPOLYLINE") (100 . "AcDbEntity") (8 . "PLANTS") (62 . 94) (370 . 13) (100 . "AcDbPolyline") (90 . 2) (70 . 0)
(43 . 0.0) (10 6176.4705882353 3680.2417420814) (10 6202.8654977376 3661.3872171946))
((0 . "LWPOLYLINE") (100 . "AcDbEntity") (8 . "PLANTS") (62 . 94) (370 . 13) (100 . "AcDbPolyline") (90 . 3) (70 . 0)
(43 . 0.0) (10 6191.553280543 3702.8661764706) (10 6177.6747737557 3691.553959276) (10 6176.4705882353 3680.2417420814))
((0 . "LWPOLYLINE") (100 . "AcDbEntity") (8 . "PLANTS") (62 . 94) (370 . 13) (100 . "AcDbPolyline") (90 . 2) (70 . 0)
(43 . 0.0) (10 6180.2410633484 995.4751131222) (10 6176.4705882353 976.6204751131))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6225.4899321267 275.2630090498 0.0) (10 6199.9424574268 292.2394035671 0.0) (10 6184.4173943683
321.5862976514 0.0) (10 6176.4705882353 350.6787330317 0.0))
((0 . "LWPOLYLINE") (100 . "AcDbEntity") (8 . "PLANTS") (62 . 94) (370 . 13) (100 . "AcDbPolyline") (90 . 3) (70 . 0)
(43 . 0.0) (10 6202.8654977376 369.5333710407) (10 6195.3176470588 368.3285067873) (10 6176.4705882353 350.6787330317))
((0 . "LWPOLYLINE") (100 . "AcDbEntity") (8 . "PLANTS") (62 . 94) (370 . 13) (100 . "AcDbPolyline") (90 . 3) (70 . 0)
(43 . 0.0) (10 6240.5734162896 1001.1312217195) (10 6214.1777149321 1010.4038461538) (10 6180.2410633484
995.4751131222))
((0 . "LWPOLYLINE") (100 . "AcDbEntity") (8 . "PLANTS") (62 . 94) (370 . 13) (100 . "AcDbPolyline") (90 . 2) (70 . 0)
(43 . 0.0) (10 6240.5734162896 1184.0130090498) (10 6235.79826546 1184.0130090498))
((0 . "LWPOLYLINE") (100 . "AcDbEntity") (8 . "PLANTS") (62 . 94) (370 . 13) (100 . "AcDbPolyline") (90 . 3) (70 . 0)
(43 . 0.0) (10 6187.7828054299 1101.0548642534) (10 6184.1600678733 1112.367081448) (10 6184.085036214 1148.7539891093))
((0 . "LWPOLYLINE") (100 . "AcDbEntity") (8 . "PLANTS") (62 . 94) (370 . 13) (100 . "AcDbPolyline") (90 . 3) (70 . 0)
(43 . 0.0) (10 6206.6367647059 3857.4660633484) (10 6192.7574660633 3872.5494343891) (10 6187.7828054299
3887.631561086))
((0 . "LWPOLYLINE") (100 . "AcDbEntity") (8 . "PLANTS") (62 . 94) (370 . 13) (100 . "AcDbPolyline") (90 . 2) (70 . 0)
(43 . 0.0) (10 6187.7828054299 3495.4751131222) (10 6195.3245475113 3484.1628959276))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6187.7828054299 3495.4751131222 0.0) (10 6190.7716958196 3494.7075359293 0.0) (10 6188.5632996965
3543.3099069247 0.0) (10 6208.4475327615 3540.1136316948 0.0))
((0 . "LWPOLYLINE") (100 . "AcDbEntity") (8 . "PLANTS") (62 . 94) (370 . 13) (100 . "AcDbPolyline") (90 . 2) (70 . 0)
(43 . 0.0) (10 6187.7828054299 1101.0548642534) (10 6195.3245475113 1097.2850678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6285.8222850679 916.2895927602 0.0) (10 6261.9302925571 908.6386637202 0.0) (10 6206.9590521059
883.1244587149 0.0) (10 6187.7828054298 916.2895927602 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6240.5734162896 1001.1312217195 0.0) (10 6243.3611823253 963.4558722169 0.0) (10 6195.4652591582
950.6247699006 0.0) (10 6187.7828054299 916.2895927602 0.0))
((0 . "LWPOLYLINE") (100 . "AcDbEntity") (8 . "PLANTS") (62 . 94) (370 . 13) (100 . "AcDbPolyline") (90 . 3) (70 . 0)
(43 . 0.0) (10 6191.553280543 3702.8661764706) (10 6195.028280543 3740.5727375566) (10 6191.553280543 3766.9683257919))
((0 . "LWPOLYLINE") (100 . "AcDbEntity") (8 . "PLANTS") (62 . 94) (370 . 13) (100 . "AcDbPolyline") (90 . 3) (70 . 0)
(43 . 0.0) (10 6210.407239819 3668.9295248869) (10 6201.6614253394 3691.553280543) (10 6191.553280543 3702.8661764706))
((0 . "LWPOLYLINE") (100 . "AcDbEntity") (8 . "PLANTS") (62 . 94) (370 . 13) (100 . "AcDbPolyline") (90 . 3) (70 . 0)
(43 . 0.0) (10 6253.7704751131 3949.8487556561) (10 6206.6367647059 3926.4022624434) (10 6195.3245475113
3929.110520362))
((0 . "LWPOLYLINE") (100 . "AcDbEntity") (8 . "PLANTS") (62 . 94) (370 . 13) (100 . "AcDbPolyline") (90 . 2) (70 . 0)
(43 . 0.0) (10 6201.6330200719 3484.1628959276) (10 6195.3245475113 3484.1628959276))
((0 . "LWPOLYLINE") (100 . "AcDbEntity") (8 . "PLANTS") (62 . 94) (370 . 13) (100 . "AcDbPolyline") (90 . 2) (70 . 0)
(43 . 0.0) (10 6194.0775773028 3465.9613276234) (10 6195.3245475113 3484.1628959276))
((0 . "LWPOLYLINE") (100 . "AcDbEntity") (8 . "PLANTS") (62 . 94) (370 . 13) (100 . "AcDbPolyline") (90 . 3) (70 . 0)
(43 . 0.0) (10 6195.3245475113 1097.2850678733) (10 6221.7194570136 1097.1366515837) (10 6236.8021493213
1089.7426470588))
((0 . "LWPOLYLINE") (100 . "AcDbEntity") (8 . "PLANTS") (62 . 94) (370 . 13) (100 . "AcDbPolyline") (90 . 2) (70 . 0)
(43 . 0.0) (10 6195.3245475113 1089.7426470588) (10 6195.3245475113 1097.2850678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6233.0316742081 3797.1338235294 0.0) (10 6209.5955841379 3797.8066914931 0.0) (10 6197.0287417314
3825.9067933911 0.0) (10 6199.0950226244 3846.1538461538 0.0))
((0 . "LWPOLYLINE") (100 . "AcDbEntity") (8 . "PLANTS") (62 . 94) (370 . 13) (100 . "AcDbPolyline") (90 . 2) (70 . 0)
(43 . 0.0) (10 6206.6367647059 3857.4660633484) (10 6199.0950226244 3846.1538461538))
((0 . "LWPOLYLINE") (100 . "AcDbEntity") (8 . "PLANTS") (62 . 94) (370 . 13) (100 . "AcDbPolyline") (90 . 2) (70 . 0)
(43 . 0.0) (10 6202.8654977376 3661.3872171946) (10 6202.8654977376 3634.9928733032))
((0 . "LWPOLYLINE") (100 . "AcDbEntity") (8 . "PLANTS") (62 . 94) (370 . 13) (100 . "AcDbPolyline") (90 . 2) (70 . 0)
(43 . 0.0) (10 6210.407239819 3668.9295248869) (10 6202.8654977376 3661.3872171946))
((0 . "LWPOLYLINE") (100 . "AcDbEntity") (8 . "PLANTS") (62 . 94) (370 . 13) (100 . "AcDbPolyline") (90 . 2) (70 . 0)
(43 . 0.0) (10 6214.1777149321 3604.8268099548) (10 6202.8654977376 3634.9928733032))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6202.8654977376 369.5333710407 0.0) (10 6208.1280669338 354.8923508198 0.0) (10 6218.7530186332
317.1290631865 0.0) (10 6244.3438914027 324.2845022624 0.0))
((0 . "LWPOLYLINE") (100 . "AcDbEntity") (8 . "PLANTS") (62 . 94) (370 . 13) (100 . "AcDbPolyline") (90 . 3) (70 . 0)
(43 . 0.0) (10 6202.8654977376 369.5333710407) (10 6203.9219457014 380.8455882353) (10 6214.1777149321 395.92760181))
((0 . "LWPOLYLINE") (100 . "AcDbEntity") (8 . "PLANTS") (62 . 94) (370 . 13) (100 . "AcDbPolyline") (90 . 2) (70 . 0)
(43 . 0.0) (10 6229.261199095 3861.2372171946) (10 6206.6367647059 3857.4660633484))
((0 . "LWPOLYLINE") (100 . "AcDbEntity") (8 . "PLANTS") (62 . 94) (370 . 13) (100 . "AcDbPolyline") (90 . 2) (70 . 0)
(43 . 0.0) (10 6210.407239819 3668.9295248869) (10 6224.136647958 3668.9295248869))
((0 . "LWPOLYLINE") (100 . "AcDbEntity") (8 . "PLANTS") (62 . 94) (370 . 13) (100 . "AcDbPolyline") (90 . 2) (70 . 0)
(43 . 0.0) (10 6233.0316742081 4144.0426470588) (10 6214.1777149321 4147.8125565611))
((0 . "LWPOLYLINE") (100 . "AcDbEntity") (8 . "PLANTS") (62 . 94) (370 . 13) (100 . "AcDbPolyline") (90 . 2) (70 . 0)
(43 . 0.0) (10 6216.3267024001 3604.8057613592) (10 6214.1777149321 3604.8268099548))
((0 . "LWPOLYLINE") (100 . "AcDbEntity") (8 . "PLANTS") (62 . 94) (370 . 13) (100 . "AcDbPolyline") (90 . 2) (70 . 0)
(43 . 0.0) (10 6214.1777149321 3587.1614432008) (10 6214.1777149321 3604.8268099548))
((0 . "LWPOLYLINE") (100 . "AcDbEntity") (8 . "PLANTS") (62 . 94) (370 . 13) (100 . "AcDbPolyline") (90 . 2) (70 . 0)
(43 . 0.0) (10 6244.3438914027 1136.8778280543) (10 6217.9489819005 1142.5339366516))
((0 . "LWPOLYLINE") (100 . "AcDbEntity") (8 . "PLANTS") (62 . 94) (370 . 13) (100 . "AcDbPolyline") (90 . 3) (70 . 0)
(43 . 0.0) (10 6229.261199095 3880.0904977376) (10 6225.4899321267 3880.0904977376) (10 6221.7194570136 3887.631561086))
((0 . "LWPOLYLINE") (100 . "AcDbEntity") (8 . "PLANTS") (62 . 94) (370 . 13) (100 . "AcDbPolyline") (90 . 2) (70 . 0)
(43 . 0.0) (10 6225.4899321267 275.2630090498) (10 6244.3438914027 275.2630090498))
((0 . "LWPOLYLINE") (100 . "AcDbEntity") (8 . "PLANTS") (62 . 94) (370 . 13) (100 . "AcDbPolyline") (90 . 2) (70 . 0)
(43 . 0.0) (10 6225.4899321267 275.2630090498) (10 6225.4899321267 233.7867647059))
((0 . "LWPOLYLINE") (100 . "AcDbEntity") (8 . "PLANTS") (62 . 94) (370 . 13) (100 . "AcDbPolyline") (90 . 3) (70 . 0)
(43 . 0.0) (10 6293.3632352941 241.3263574661) (10 6255.6561085973 233.9338235294) (10 6225.4899321267 233.7867647059))
((0 . "LWPOLYLINE") (100 . "AcDbEntity") (8 . "PLANTS") (62 . 94) (370 . 13) (100 . "AcDbPolyline") (90 . 2) (70 . 0)
(43 . 0.0) (10 6229.261199095 4008.296040724) (10 6236.8021493213 4008.296040724))
((0 . "LWPOLYLINE") (100 . "AcDbEntity") (8 . "PLANTS") (62 . 94) (370 . 13) (100 . "AcDbPolyline") (90 . 2) (70 . 0)
(43 . 0.0) (10 6229.261199095 3880.0904977376) (10 6229.261199095 3861.2372171946))
((0 . "LWPOLYLINE") (100 . "AcDbEntity") (8 . "PLANTS") (62 . 94) (370 . 13) (100 . "AcDbPolyline") (90 . 2) (70 . 0)
(43 . 0.0) (10 6259.4265837104 3883.8616515837) (10 6229.261199095 3880.0904977376))
((0 . "LWPOLYLINE") (100 . "AcDbEntity") (8 . "PLANTS") (62 . 94) (370 . 13) (100 . "AcDbPolyline") (90 . 3) (70 . 0)
(43 . 0.0) (10 6263.1978506787 3857.4660633484) (10 6236.8090497738 3857.6141402715) (10 6229.261199095
3861.2372171946))
((0 . "LWPOLYLINE") (100 . "AcDbEntity") (8 . "PLANTS") (62 . 94) (370 . 13) (100 . "AcDbPolyline") (90 . 2) (70 . 0)
(43 . 0.0) (10 6233.0316742081 4144.0426470588) (10 6236.8021493213 4095.0226244344))
((0 . "LWPOLYLINE") (100 . "AcDbEntity") (8 . "PLANTS") (62 . 94) (370 . 13) (100 . "AcDbPolyline") (90 . 3) (70 . 0)
(43 . 0.0) (10 6240.5734162896 4151.5837104072) (10 6236.8021493213 4151.5837104072) (10 6233.0316742081
4144.0426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6233.0316742081 3797.1338235294 0.0) (10 6230.4826544471 3776.8027896235 0.0) (10 6232.9280743487
3745.6490782077 0.0) (10 6255.6561085973 3736.8028280543 0.0))
((0 . "LWPOLYLINE") (100 . "AcDbEntity") (8 . "PLANTS") (62 . 94) (370 . 13) (100 . "AcDbPolyline") (90 . 2) (70 . 0)
(43 . 0.0) (10 6233.0316742081 3797.1338235294) (10 6285.8222850679 3800.9049773756))
((0 . "LWPOLYLINE") (100 . "AcDbEntity") (8 . "PLANTS") (62 . 94) (370 . 13) (100 . "AcDbPolyline") (90 . 3) (70 . 0)
(43 . 0.0) (10 6240.5734162896 4151.5837104072) (10 6236.8083710407 4166.667081448) (10 6236.8077642497
4254.1920110471))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6315.9876696833 4068.6270361991 0.0) (10 6284.9695617397 4069.8943500595 0.0) (10 6272.6041347291
4112.5892062519 0.0) (10 6236.8021493213 4095.0226244344 0.0))
((0 . "LWPOLYLINE") (100 . "AcDbEntity") (8 . "PLANTS") (62 . 94) (370 . 13) (100 . "AcDbPolyline") (90 . 2) (70 . 0)
(43 . 0.0) (10 6236.8021493213 4027.149321267) (10 6236.8021493213 4095.0226244344))
((0 . "LWPOLYLINE") (100 . "AcDbEntity") (8 . "PLANTS") (62 . 94) (370 . 13) (100 . "AcDbPolyline") (90 . 2) (70 . 0)
(43 . 0.0) (10 6236.8021493213 4027.149321267) (10 6236.8021493213 4008.296040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6300.9049773756 4019.6082579186 0.0) (10 6291.2759049577 4046.113158262 0.0) (10 6255.5211277807
4035.0649231229 0.0) (10 6236.8021493213 4027.149321267 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6253.7704751131 3949.8487556561 0.0) (10 6237.5549593187 3966.3354230533 0.0) (10 6258.9589056904
3994.1705512976 0.0) (10 6236.8021493213 4008.296040724 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6240.5734162896 1001.1312217195 0.0) (10 6250.8982937266 1032.0032237223 0.0) (10 6225.5011494173
1059.125756363 0.0) (10 6236.8021493213 1089.7426470588 0.0))
((0 . "LWPOLYLINE") (100 . "AcDbEntity") (8 . "PLANTS") (62 . 94) (370 . 13) (100 . "AcDbPolyline") (90 . 2) (70 . 0)
(43 . 0.0) (10 6244.3438914027 1093.5152714932) (10 6236.8021493213 1089.7426470588))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.2793350987)
(40 . 0.3724312317) (40 . 0.4548274916) (40 . 1) (40 . 1) (40 . 1) (40 . 1) (10 6236.8021493213 361.9909502262 0.0) (10
6245.8989915565 343.9567360932 0.0) (10 6273.4823602063 348.3937339813 0.0) (10 6293.9394047579 331.3794626058 0.0) (10
6332.6777070312 316.2288922228 0.0) (10 6361.2679756314 279.5115889897 0.0) (10 6397.0588235294 286.5752262443 0.0))
((0 . "LWPOLYLINE") (100 . "AcDbEntity") (8 . "PLANTS") (62 . 94) (370 . 13) (100 . "AcDbPolyline") (90 . 2) (70 . 0)
(43 . 0.0) (10 6240.5734162896 4151.5837104072) (10 6259.4265837104 4140.2714932127))
((0 . "LWPOLYLINE") (100 . "AcDbEntity") (8 . "PLANTS") (62 . 94) (370 . 13) (100 . "AcDbPolyline") (90 . 3) (70 . 0)
(43 . 0.0) (10 6244.3438914027 1136.8778280543) (10 6244.1961538462 1172.7007918552) (10 6240.5734162896
1184.0130090498))
((0 . "LWPOLYLINE") (100 . "AcDbEntity") (8 . "PLANTS") (62 . 94) (370 . 13) (100 . "AcDbPolyline") (90 . 2) (70 . 0)
(43 . 0.0) (10 6244.5521980015 1189.981599419) (10 6240.5734162896 1184.0130090498))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6240.5734162896 1001.1312217195 0.0) (10 6267.1586616403 994.3312132952 0.0) (10 6284.9679129592
1040.0180119753 0.0) (10 6315.9876696833 1006.7873303167 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6244.3438914027 1136.8778280543 0.0) (10 6275.4316432241 1140.4092430644 0.0) (10 6317.4094955263
1117.6321328056 0.0) (10 6315.9876696833 1082.2030542986 0.0))
((0 . "LWPOLYLINE") (100 . "AcDbEntity") (8 . "PLANTS") (62 . 94) (370 . 13) (100 . "AcDbPolyline") (90 . 3) (70 . 0)
(43 . 0.0) (10 6244.3438914027 1136.8778280543) (10 6240.5734162896 1116.1397058824) (10 6244.3438914027
1093.5152714932))
((0 . "LWPOLYLINE") (100 . "AcDbEntity") (8 . "PLANTS") (62 . 94) (370 . 13) (100 . "AcDbPolyline") (90 . 2) (70 . 0)
(43 . 0.0) (10 6244.3438914027 1093.5152714932) (10 6315.9876696833 1082.2030542986))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6244.3438914027 437.4066742081 0.0) (10 6232.106143315 425.2194629125 0.0) (10 6235.0366647515
398.3320516588 0.0) (10 6251.8856334842 392.1578054299 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6315.9876696833 279.0356334841 0.0) (10 6305.8401041296 315.4364289921 0.0) (10 6244.6632910834
317.3500763167 0.0) (10 6244.3438914027 275.2630090497 0.0))
((0 . "LWPOLYLINE") (100 . "AcDbEntity") (8 . "PLANTS") (62 . 94) (370 . 13) (100 . "AcDbPolyline") (90 . 3) (70 . 0)
(43 . 0.0) (10 6244.3438914027 275.2630090498) (10 6266.9683257919 278.7386877828) (10 6278.2805429864 275.2630090498))
((0 . "LWPOLYLINE") (100 . "AcDbEntity") (8 . "PLANTS") (62 . 94) (370 . 13) (100 . "AcDbPolyline") (90 . 3) (70 . 0)
(43 . 0.0) (10 6251.6486461683 1194.8200868054) (10 6274.5100678733 1191.55260181) (10 6300.9049773756 1195.3252262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6304.6754524887 456.2584841629 0.0) (10 6291.8532065316 458.6895452683 0.0) (10 6270.734675807
467.8825706624 0.0) (10 6271.4528948841 483.788003286 0.0))
((0 . "LWPOLYLINE") (100 . "AcDbEntity") (8 . "PLANTS") (62 . 94) (370 . 13) (100 . "AcDbPolyline") (90 . 2) (70 . 0)
(43 . 0.0) (10 6253.7704751131 3949.8487556561) (10 6263.1978506787 3932.8804298643))
((0 . "LWPOLYLINE") (100 . "AcDbEntity") (8 . "PLANTS") (62 . 94) (370 . 13) (100 . "AcDbPolyline") (90 . 3) (70 . 0)
(43 . 0.0) (10 6253.7704751131 3949.8487556561) (10 6274.5100678733 3965.6197963801) (10 6297.1345022624
3974.3593891403))
((0 . "LWPOLYLINE") (100 . "AcDbEntity") (8 . "PLANTS") (62 . 94) (370 . 13) (100 . "AcDbPolyline") (90 . 2) (70 . 0)
(43 . 0.0) (10 6256.410253388 3733.0316742081) (10 6255.6561085973 3736.8028280543))
((0 . "LWPOLYLINE") (100 . "AcDbEntity") (8 . "PLANTS") (62 . 94) (370 . 13) (100 . "AcDbPolyline") (90 . 2) (70 . 0)
(43 . 0.0) (10 6289.592760181 3782.0516968326) (10 6255.6561085973 3736.8028280543))
((0 . "LWPOLYLINE") (100 . "AcDbEntity") (8 . "PLANTS") (62 . 94) (370 . 13) (100 . "AcDbPolyline") (90 . 2) (70 . 0)
(43 . 0.0) (10 6259.4265837104 3883.8616515837) (10 6263.1978506787 3857.4660633484))
((0 . "LWPOLYLINE") (100 . "AcDbEntity") (8 . "PLANTS") (62 . 94) (370 . 13) (100 . "AcDbPolyline") (90 . 2) (70 . 0)
(43 . 0.0) (10 6259.4265837104 3883.8616515837) (10 6263.1978506787 3932.8804298643))
((0 . "LWPOLYLINE") (100 . "AcDbEntity") (8 . "PLANTS") (62 . 94) (370 . 13) (100 . "AcDbPolyline") (90 . 3) (70 . 0)
(43 . 0.0) (10 6335.3617341176 3724.4499590952) (10 6338.6121040724 3725.3421945701) (10 6368.778280543
3725.4906108597))
((0 . "LWPOLYLINE") (100 . "AcDbEntity") (8 . "PLANTS") (62 . 94) (370 . 13) (100 . "AcDbPolyline") (90 . 2) (70 . 0)
(43 . 0.0) (10 6263.1978506787 3932.8804298643) (10 6312.2171945701 3932.8804298643))
((0 . "LWPOLYLINE") (100 . "AcDbEntity") (8 . "PLANTS") (62 . 94) (370 . 13) (100 . "AcDbPolyline") (90 . 2) (70 . 0)
(43 . 0.0) (10 6263.1978506787 3857.4660633484) (10 6285.8222850679 3831.0704751131))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6349.3571216503 3580.4974016159 0.0) (10 6364.0637653495 3585.8156709405 0.0) (10 6344.3773117082
3612.0106876064 0.0) (10 6365.0078054299 3616.1390271493 0.0))
((0 . "LWPOLYLINE") (100 . "AcDbEntity") (8 . "PLANTS") (62 . 94) (370 . 13) (100 . "AcDbPolyline") (90 . 2) (70 . 0)
(43 . 0.0) (10 6285.8222850679 3831.0704751131) (10 6285.8222850679 3800.9049773756))
((0 . "LWPOLYLINE") (100 . "AcDbEntity") (8 . "PLANTS") (62 . 94) (370 . 13) (100 . "AcDbPolyline") (90 . 2) (70 . 0)
(43 . 0.0) (10 6285.8222850679 3831.0704751131) (10 6312.2171945701 3834.8416289593))
((0 . "LWPOLYLINE") (100 . "AcDbEntity") (8 . "PLANTS") (62 . 94) (370 . 13) (100 . "AcDbPolyline") (90 . 2) (70 . 0)
(43 . 0.0) (10 6289.592760181 3782.0516968326) (10 6285.8222850679 3800.9049773756))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6285.8222850679 916.2895927602 0.0) (10 6302.1314586373 892.6360391352 0.0) (10 6343.9859374158
888.8214438643 0.0) (10 6361.2365384615 912.5197963801 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6285.8222850679 916.2895927602 0.0) (10 6277.6033367169 969.1695421872 0.0) (10 6361.6374744953
964.8118179128 0.0) (10 6361.2365384615 912.5197963801 0.0))
((0 . "LWPOLYLINE") (100 . "AcDbEntity") (8 . "PLANTS") (62 . 94) (370 . 13) (100 . "AcDbPolyline") (90 . 2) (70 . 0)
(43 . 0.0) (10 6342.3833710407 3785.8216063348) (10 6289.592760181 3782.0516968326))
((0 . "LWPOLYLINE") (100 . "AcDbEntity") (8 . "PLANTS") (62 . 94) (370 . 13) (100 . "AcDbPolyline") (90 . 2) (70 . 0)
(43 . 0.0) (10 6289.592760181 267.7234162896) (10 6293.3632352941 241.3263574661))
((0 . "LWPOLYLINE") (100 . "AcDbEntity") (8 . "PLANTS") (62 . 94) (370 . 13) (100 . "AcDbPolyline") (90 . 3) (70 . 0)
(43 . 0.0) (10 6293.3632352941 241.3263574661) (10 6372.5487556561 237.5627828054) (10 6395.1731900452 245.0989819005))
((0 . "LWPOLYLINE") (100 . "AcDbEntity") (8 . "PLANTS") (62 . 94) (370 . 13) (100 . "AcDbPolyline") (90 . 2) (70 . 0)
(43 . 0.0) (10 6297.1345022624 3974.3593891403) (10 6319.7589366516 3959.2760180995))
((0 . "LWPOLYLINE") (100 . "AcDbEntity") (8 . "PLANTS") (62 . 94) (370 . 13) (100 . "AcDbPolyline") (90 . 3) (70 . 0)
(43 . 0.0) (10 6300.9049773756 4019.6082579186) (10 6297.282239819 4008.295361991) (10 6297.1345022624 3974.3593891403))
((0 . "LWPOLYLINE") (100 . "AcDbEntity") (8 . "PLANTS") (62 . 94) (370 . 13) (100 . "AcDbPolyline") (90 . 2) (70 . 0)
(43 . 0.0) (10 6338.6121040724 4023.3781674208) (10 6300.9049773756 4019.6082579186))
((0 . "LWPOLYLINE") (100 . "AcDbEntity") (8 . "PLANTS") (62 . 94) (370 . 13) (100 . "AcDbPolyline") (90 . 2) (70 . 0)
(43 . 0.0) (10 6300.9049773756 1228.4039489922) (10 6300.9049773756 1195.3252262443))
((0 . "LWPOLYLINE") (100 . "AcDbEntity") (8 . "PLANTS") (62 . 94) (370 . 13) (100 . "AcDbPolyline") (90 . 3) (70 . 0)
(43 . 0.0) (10 6323.5294117647 1172.7007918552) (10 6312.3649321267 1176.6252262443) (10 6300.9049773756
1195.3252262443))
((0 . "LWPOLYLINE") (100 . "AcDbEntity") (8 . "PLANTS") (62 . 94) (370 . 13) (100 . "AcDbPolyline") (90 . 3) (70 . 0)
(43 . 0.0) (10 6327.2998868778 4083.7104072398) (10 6304.6816742081 4151.5837104072) (10 6304.6794810001
4305.1082714306))
((0 . "LWPOLYLINE") (100 . "AcDbEntity") (8 . "PLANTS") (62 . 94) (370 . 13) (100 . "AcDbPolyline") (90 . 2) (70 . 0)
(43 . 0.0) (10 6308.446719457 448.7188914027) (10 6304.6754524887 456.2584841629))
((0 . "LWPOLYLINE") (100 . "AcDbEntity") (8 . "PLANTS") (62 . 94) (370 . 13) (100 . "AcDbPolyline") (90 . 2) (70 . 0)
(43 . 0.0) (10 6319.7589366516 467.5707013575) (10 6304.6754524887 456.2584841629))
((0 . "LWPOLYLINE") (100 . "AcDbEntity") (8 . "PLANTS") (62 . 94) (370 . 13) (100 . "AcDbPolyline") (90 . 2) (70 . 0)
(43 . 0.0) (10 6304.6754524887 358.2211538462) (10 6342.3833710407 358.2211538462))
((0 . "LWPOLYLINE") (100 . "AcDbEntity") (8 . "PLANTS") (62 . 94) (370 . 13) (100 . "AcDbPolyline") (90 . 2) (70 . 0)
(43 . 0.0) (10 6315.9876696833 3891.4027149321) (10 6312.2171945701 3932.8804298643))
((0 . "LWPOLYLINE") (100 . "AcDbEntity") (8 . "PLANTS") (62 . 94) (370 . 13) (100 . "AcDbPolyline") (90 . 2) (70 . 0)
(43 . 0.0) (10 6312.2171945701 3932.8804298643) (10 6319.7589366516 3959.2760180995))
((0 . "LWPOLYLINE") (100 . "AcDbEntity") (8 . "PLANTS") (62 . 94) (370 . 13) (100 . "AcDbPolyline") (90 . 2) (70 . 0)
(43 . 0.0) (10 6346.1538461538 3834.8416289593) (10 6312.2171945701 3834.8416289593))
((0 . "LWPOLYLINE") (100 . "AcDbEntity") (8 . "PLANTS") (62 . 94) (370 . 13) (100 . "AcDbPolyline") (90 . 3) (70 . 0)
(43 . 0.0) (10 6315.9876696833 3891.4027149321) (10 6308.5951357466 3865.0071266968) (10 6312.2171945701
3834.8416289593))
((0 . "LWPOLYLINE") (100 . "AcDbEntity") (8 . "PLANTS") (62 . 94) (370 . 13) (100 . "AcDbPolyline") (90 . 2) (70 . 0)
(43 . 0.0) (10 6315.9876696833 1006.7873303167) (10 6312.2171945701 1025.6419683258))
((0 . "LWPOLYLINE") (100 . "AcDbEntity") (8 . "PLANTS") (62 . 94) (370 . 13) (100 . "AcDbPolyline") (90 . 2) (70 . 0)
(43 . 0.0) (10 6315.9876696833 3891.4027149321) (10 6338.6121040724 3891.4027149321))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6380.0904977376 1036.9541855204 0.0) (10 6352.8005276039 1039.8294247346 0.0) (10 6330.742798059
1060.4673346996 0.0) (10 6315.9876696833 1082.2030542986 0.0))
((0 . "LWPOLYLINE") (100 . "AcDbEntity") (8 . "PLANTS") (62 . 94) (370 . 13) (100 . "AcDbPolyline") (90 . 3) (70 . 0)
(43 . 0.0) (10 6383.8609728507 961.5384615385) (10 6353.6955882353 970.2842760181) (10 6315.9876696833 1006.7873303167))
((0 . "LWPOLYLINE") (100 . "AcDbEntity") (8 . "PLANTS") (62 . 94) (370 . 13) (100 . "AcDbPolyline") (90 . 2) (70 . 0)
(43 . 0.0) (10 6315.9876696833 478.882918552) (10 6319.7589366516 467.5707013575))
((0 . "LWPOLYLINE") (100 . "AcDbEntity") (8 . "PLANTS") (62 . 94) (370 . 13) (100 . "AcDbPolyline") (90 . 2) (70 . 0)
(43 . 0.0) (10 6319.7589366516 3959.2760180995) (10 6338.6121040724 3959.2760180995))
((0 . "LWPOLYLINE") (100 . "AcDbEntity") (8 . "PLANTS") (62 . 94) (370 . 13) (100 . "AcDbPolyline") (90 . 2) (70 . 0)
(43 . 0.0) (10 6365.0078054299 441.1764705882) (10 6319.7589366516 467.5707013575))
((0 . "LWPOLYLINE") (100 . "AcDbEntity") (8 . "PLANTS") (62 . 94) (370 . 13) (100 . "AcDbPolyline") (90 . 3) (70 . 0)
(43 . 0.0) (10 6349.924321267 1089.7426470588) (10 6348.8679864253 1104.8274886878) (10 6323.5294117647
1172.7007918552))
((0 . "LWPOLYLINE") (100 . "AcDbEntity") (8 . "PLANTS") (62 . 94) (370 . 13) (100 . "AcDbPolyline") (90 . 3) (70 . 0)
(43 . 0.0) (10 6323.5294117647 1172.7007918552) (10 6338.6121040724 1177.6685520362) (10 6365.0078054299
1199.0950226244))
((0 . "LWPOLYLINE") (100 . "AcDbEntity") (8 . "PLANTS") (62 . 94) (370 . 13) (100 . "AcDbPolyline") (90 . 2) (70 . 0)
(43 . 0.0) (10 6334.8416289593 392.1578054299) (10 6342.3833710407 388.3851809955))
((0 . "LWPOLYLINE") (100 . "AcDbEntity") (8 . "PLANTS") (62 . 94) (370 . 13) (100 . "AcDbPolyline") (90 . 3) (70 . 0)
(43 . 0.0) (10 6338.6121040724 4023.3781674208) (10 6338.6121040724 4019.6082579186) (10 6349.924321267
4012.0659502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6338.6121040724 4023.3781674208 0.0) (10 6337.7811667375 4063.5519460523 0.0) (10 6389.824253776
4042.1153195846 0.0) (10 6376.3200226244 4012.0659502262 0.0))
((0 . "LWPOLYLINE") (100 . "AcDbEntity") (8 . "PLANTS") (62 . 94) (370 . 13) (100 . "AcDbPolyline") (90 . 2) (70 . 0)
(43 . 0.0) (10 6361.2365384615 3951.7349547511) (10 6338.6121040724 3959.2760180995))
((0 . "LWPOLYLINE") (100 . "AcDbEntity") (8 . "PLANTS") (62 . 94) (370 . 13) (100 . "AcDbPolyline") (90 . 3) (70 . 0)
(43 . 0.0) (10 6349.924321267 4012.0659502262) (10 6338.759841629 3974.3593891403) (10 6338.6121040724 3959.2760180995))
((0 . "LWPOLYLINE") (100 . "AcDbEntity") (8 . "PLANTS") (62 . 94) (370 . 13) (100 . "AcDbPolyline") (90 . 3) (70 . 0)
(43 . 0.0) (10 6346.1538461538 3834.8416289593) (10 6346.0061085973 3861.2372171946) (10 6338.6121040724
3891.4027149321))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6436.6515837104 3940.4227375566 0.0) (10 6398.4662852462 3939.6047390151 0.0) (10 6363.6726574247
3918.8784590591 0.0) (10 6338.6121040724 3891.4027149321 0.0))
((0 . "LWPOLYLINE") (100 . "AcDbEntity") (8 . "PLANTS") (62 . 94) (370 . 13) (100 . "AcDbPolyline") (90 . 2) (70 . 0)
(43 . 0.0) (10 6342.3833710407 3785.8216063348) (10 6368.778280543 3736.8028280543))
((0 . "LWPOLYLINE") (100 . "AcDbEntity") (8 . "PLANTS") (62 . 94) (370 . 13) (100 . "AcDbPolyline") (90 . 3) (70 . 0)
(43 . 0.0) (10 6342.3833710407 3785.8216063348) (10 6343.4328054299 3800.9049773756) (10 6353.6955882353
3831.0704751131))
((0 . "LWPOLYLINE") (100 . "AcDbEntity") (8 . "PLANTS") (62 . 94) (370 . 13) (100 . "AcDbPolyline") (90 . 2) (70 . 0)
(43 . 0.0) (10 6342.3833710407 358.2211538462) (10 6342.3833710407 388.3851809955))
((0 . "LWPOLYLINE") (100 . "AcDbEntity") (8 . "PLANTS") (62 . 94) (370 . 13) (100 . "AcDbPolyline") (90 . 2) (70 . 0)
(43 . 0.0) (10 6365.0078054299 403.4700226244) (10 6342.3833710407 388.3851809955))
((0 . "LWPOLYLINE") (100 . "AcDbEntity") (8 . "PLANTS") (62 . 94) (370 . 13) (100 . "AcDbPolyline") (90 . 3) (70 . 0)
(43 . 0.0) (10 6398.9444570136 320.5118778281) (10 6372.5487556561 333.0227375566) (10 6342.3833710407 358.2211538462))
((0 . "LWPOLYLINE") (100 . "AcDbEntity") (8 . "PLANTS") (62 . 94) (370 . 13) (100 . "AcDbPolyline") (90 . 2) (70 . 0)
(43 . 0.0) (10 6346.1538461538 3834.8416289593) (10 6353.6955882353 3831.0704751131))
((0 . "LWPOLYLINE") (100 . "AcDbEntity") (8 . "PLANTS") (62 . 94) (370 . 13) (100 . "AcDbPolyline") (90 . 2) (70 . 0)
(43 . 0.0) (10 6349.924321267 3676.4705882353) (10 6346.1538461538 3687.7828054299))
((0 . "LWPOLYLINE") (100 . "AcDbEntity") (8 . "PLANTS") (62 . 94) (370 . 13) (100 . "AcDbPolyline") (90 . 2) (70 . 0)
(43 . 0.0) (10 6349.924321267 4012.0659502262) (10 6376.3200226244 4012.0659502262))
((0 . "LWPOLYLINE") (100 . "AcDbEntity") (8 . "PLANTS") (62 . 94) (370 . 13) (100 . "AcDbPolyline") (90 . 2) (70 . 0)
(43 . 0.0) (10 6353.6955882353 3831.0704751131) (10 6368.778280543 3834.8416289593))
((0 . "LWPOLYLINE") (100 . "AcDbEntity") (8 . "PLANTS") (62 . 94) (370 . 13) (100 . "AcDbPolyline") (90 . 3) (70 . 0)
(43 . 0.0) (10 6361.2365384615 4083.7104072398) (10 6366.0641402715 4110.1053167421) (10 6376.3200226244
4121.4182126697))
((0 . "LWPOLYLINE") (100 . "AcDbEntity") (8 . "PLANTS") (62 . 94) (370 . 13) (100 . "AcDbPolyline") (90 . 2) (70 . 0)
(43 . 0.0) (10 6361.2365384615 3631.221719457) (10 6365.0078054299 3616.1390271493))
((0 . "LWPOLYLINE") (100 . "AcDbEntity") (8 . "PLANTS") (62 . 94) (370 . 13) (100 . "AcDbPolyline") (90 . 2) (70 . 0)
(43 . 0.0) (10 6380.0904977376 912.5197963801) (10 6361.2365384615 912.5197963801))
((0 . "LWPOLYLINE") (100 . "AcDbEntity") (8 . "PLANTS") (62 . 94) (370 . 13) (100 . "AcDbPolyline") (90 . 2) (70 . 0)
(43 . 0.0) (10 6402.7149321267 3616.1390271493) (10 6365.0078054299 3616.1390271493))
((0 . "LWPOLYLINE") (100 . "AcDbEntity") (8 . "PLANTS") (62 . 94) (370 . 13) (100 . "AcDbPolyline") (90 . 2) (70 . 0)
(43 . 0.0) (10 6365.0078054299 1262.9989878543) (10 6365.0078054299 1199.0950226244))
((0 . "LWPOLYLINE") (100 . "AcDbEntity") (8 . "PLANTS") (62 . 94) (370 . 13) (100 . "AcDbPolyline") (90 . 3) (70 . 0)
(43 . 0.0) (10 6365.0078054299 1199.0950226244) (10 6383.861199095 1187.7828054299) (10 6383.861199095 1168.9281674208))
((0 . "LWPOLYLINE") (100 . "AcDbEntity") (8 . "PLANTS") (62 . 94) (370 . 13) (100 . "AcDbPolyline") (90 . 2) (70 . 0)
(43 . 0.0) (10 6365.0078054299 441.1764705882) (10 6383.8609728507 441.1764705882))
((0 . "LWPOLYLINE") (100 . "AcDbEntity") (8 . "PLANTS") (62 . 94) (370 . 13) (100 . "AcDbPolyline") (90 . 2) (70 . 0)
(43 . 0.0) (10 6365.0078054299 441.1764705882) (10 6365.0078054299 403.4700226244))
((0 . "LWPOLYLINE") (100 . "AcDbEntity") (8 . "PLANTS") (62 . 94) (370 . 13) (100 . "AcDbPolyline") (90 . 3) (70 . 0)
(43 . 0.0) (10 6417.7976244344 346.9089366516) (10 6387.4837104072 384.6153846154) (10 6365.0078054299 403.4700226244))
((0 . "LWPOLYLINE") (100 . "AcDbEntity") (8 . "PLANTS") (62 . 94) (370 . 13) (100 . "AcDbPolyline") (90 . 2) (70 . 0)
(43 . 0.0) (10 6380.0904977376 3891.4027149321) (10 6368.778280543 3891.4027149321))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6368.778280543 3834.8416289593 0.0) (10 6394.7785046575 3802.9412568728 0.0) (10 6449.3551079717
3825.4705475686 0.0) (10 6481.9004524887 3842.3826923077 0.0))
((0 . "LWPOLYLINE") (100 . "AcDbEntity") (8 . "PLANTS") (62 . 94) (370 . 13) (100 . "AcDbPolyline") (90 . 3) (70 . 0)
(43 . 0.0) (10 6414.0271493213 3883.8616515837) (10 6388.6816742081 3861.088800905) (10 6368.778280543 3834.8416289593))
((0 . "LWPOLYLINE") (100 . "AcDbEntity") (8 . "PLANTS") (62 . 94) (370 . 13) (100 . "AcDbPolyline") (90 . 3) (70 . 0)
(43 . 0.0) (10 6368.778280543 3736.8028280543) (10 6398.9444570136 3735.7461538462) (10 6429.109841629 3721.7194570136))
((0 . "LWPOLYLINE") (100 . "AcDbEntity") (8 . "PLANTS") (62 . 94) (370 . 13) (100 . "AcDbPolyline") (90 . 2) (70 . 0)
(43 . 0.0) (10 6368.778280543 3736.8028280543) (10 6368.778280543 3725.4906108597))
((0 . "LWPOLYLINE") (100 . "AcDbEntity") (8 . "PLANTS") (62 . 94) (370 . 13) (100 . "AcDbPolyline") (90 . 2) (70 . 0)
(43 . 0.0) (10 6383.8609728507 3702.8661764706) (10 6368.778280543 3725.4906108597))
((0 . "LWPOLYLINE") (100 . "AcDbEntity") (8 . "PLANTS") (62 . 94) (370 . 13) (100 . "AcDbPolyline") (90 . 3) (70 . 0)
(43 . 0.0) (10 6376.5431402273 4335.9069825279) (10 6376.3262443439 4272.2469457014) (10 6380.0904977376
4253.3936651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6414.0271493212 4053.5449095023 0.0) (10 6390.2923541344 4069.618836943 0.0) (10 6414.4664214512
4115.085397383 0.0) (10 6376.3200226244 4121.4182126697 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6380.0904977376 4253.3936651584 0.0) (10 6327.7381154426 4233.2955461527 0.0) (10 6384.6216862745
4139.1034787646 0.0) (10 6376.3200226244 4121.4182126697 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6429.109841629 3974.3593891403 0.0) (10 6402.9970916857 3969.4180461516 0.0) (10 6385.860247208
3992.243689016 0.0) (10 6376.3200226244 4012.0659502262 0.0))
((0 . "LWPOLYLINE") (100 . "AcDbEntity") (8 . "PLANTS") (62 . 94) (370 . 13) (100 . "AcDbPolyline") (90 . 2) (70 . 0)
(43 . 0.0) (10 6376.3200226244 1142.5339366516) (10 6383.861199095 1168.9281674208))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6380.0904977377 4253.3936651584 0.0) (10 6400.6549325084 4229.5578996289 0.0) (10 6404.3312929856
4181.5711869438 0.0) (10 6447.9638009051 4185.520361991 0.0))
((0 . "LWPOLYLINE") (100 . "AcDbEntity") (8 . "PLANTS") (62 . 94) (370 . 13) (100 . "AcDbPolyline") (90 . 2) (70 . 0)
(43 . 0.0) (10 6391.4027149321 3657.6173076923) (10 6380.0904977376 3650.075))
((0 . "LWPOLYLINE") (100 . "AcDbEntity") (8 . "PLANTS") (62 . 94) (370 . 13) (100 . "AcDbPolyline") (90 . 3) (70 . 0)
(43 . 0.0) (10 6398.9444570136 1070.8908371041) (10 6385.0589366516 1085.9728506787) (10 6380.0904977376
1101.0548642534))
((0 . "LWPOLYLINE") (100 . "AcDbEntity") (8 . "PLANTS") (62 . 94) (370 . 13) (100 . "AcDbPolyline") (90 . 3) (70 . 0)
(43 . 0.0) (10 6391.4027149321 972.850678733) (10 6384.0087104072 999.2449095023) (10 6380.0904977376 1036.9541855204))
((0 . "LWPOLYLINE") (100 . "AcDbEntity") (8 . "PLANTS") (62 . 94) (370 . 13) (100 . "AcDbPolyline") (90 . 3) (70 . 0)
(43 . 0.0) (10 6380.0904977376 1036.9541855204) (10 6387.6384615385 1043.2966063348) (10 6398.9444570136
1044.4937782805))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6380.0904977376 912.5197963801 0.0) (10 6396.7677564501 892.2329090796 0.0) (10 6430.4368059942
892.7338822926 0.0) (10 6451.7342760181 904.9773755656 0.0))
((0 . "LWPOLYLINE") (100 . "AcDbEntity") (8 . "PLANTS") (62 . 94) (370 . 13) (100 . "AcDbPolyline") (90 . 2) (70 . 0)
(43 . 0.0) (10 6380.0904977376 912.5197963801) (10 6383.8609728507 961.5384615385))
((0 . "LWPOLYLINE") (100 . "AcDbEntity") (8 . "PLANTS") (62 . 94) (370 . 13) (100 . "AcDbPolyline") (90 . 2) (70 . 0)
(43 . 0.0) (10 6383.8609728507 3702.8661764706) (10 6391.4027149321 3657.6173076923))
((0 . "LWPOLYLINE") (100 . "AcDbEntity") (8 . "PLANTS") (62 . 94) (370 . 13) (100 . "AcDbPolyline") (90 . 2) (70 . 0)
(43 . 0.0) (10 6383.8609728507 3702.8661764706) (10 6402.7149321267 3706.6360859729))
((0 . "LWPOLYLINE") (100 . "AcDbEntity") (8 . "PLANTS") (62 . 94) (370 . 13) (100 . "AcDbPolyline") (90 . 2) (70 . 0)
(43 . 0.0) (10 6391.4027149321 972.850678733) (10 6383.8609728507 961.5384615385))
((0 . "LWPOLYLINE") (100 . "AcDbEntity") (8 . "PLANTS") (62 . 94) (370 . 13) (100 . "AcDbPolyline") (90 . 3) (70 . 0)
(43 . 0.0) (10 6383.8609728507 441.1764705882) (10 6427.9119909502 380.8455882353) (10 6432.8811085973 365.7607466063))
((0 . "LWPOLYLINE") (100 . "AcDbEntity") (8 . "PLANTS") (62 . 94) (370 . 13) (100 . "AcDbPolyline") (90 . 3) (70 . 0)
(43 . 0.0) (10 6395.1731900452 482.6555429864) (10 6397.7402714932 467.5707013575) (10 6383.8609728507 441.1764705882))
((0 . "LWPOLYLINE") (100 . "AcDbEntity") (8 . "PLANTS") (62 . 94) (370 . 13) (100 . "AcDbPolyline") (90 . 2) (70 . 0)
(43 . 0.0) (10 6414.0271493213 1168.9281674208) (10 6383.861199095 1168.9281674208))
((0 . "LWPOLYLINE") (100 . "AcDbEntity") (8 . "PLANTS") (62 . 94) (370 . 13) (100 . "AcDbPolyline") (90 . 3) (70 . 0)
(43 . 0.0) (10 6430.9954751131 3633.1066742081) (10 6414.0271493213 3649.0195701357) (10 6391.4027149321
3657.6173076923))
((0 . "LWPOLYLINE") (100 . "AcDbEntity") (8 . "PLANTS") (62 . 94) (370 . 13) (100 . "AcDbPolyline") (90 . 3) (70 . 0)
(43 . 0.0) (10 6391.4027149321 972.850678733) (10 6432.8811085973 972.7022624434) (10 6447.963800905 965.3082579186))
((0 . "LWPOLYLINE") (100 . "AcDbEntity") (8 . "PLANTS") (62 . 94) (370 . 13) (100 . "AcDbPolyline") (90 . 3) (70 . 0)
(43 . 0.0) (10 6414.0271493213 3883.8616515837) (10 6406.3314479638 3897.7464932127) (10 6395.1731900452
3902.7149321267))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6395.1731900452 245.0989819005 0.0) (10 6419.0708113038 231.5170237362 0.0) (10 6456.3923190679
229.9117302652 0.0) (10 6470.5882352941 260.1809954751 0.0))
((0 . "LWPOLYLINE") (100 . "AcDbEntity") (8 . "PLANTS") (62 . 94) (370 . 13) (100 . "AcDbPolyline") (90 . 2) (70 . 0)
(43 . 0.0) (10 6395.1731900452 245.0989819005) (10 6397.0588235294 286.5752262443))
((0 . "LWPOLYLINE") (100 . "AcDbEntity") (8 . "PLANTS") (62 . 94) (370 . 13) (100 . "AcDbPolyline") (90 . 3) (70 . 0)
(43 . 0.0) (10 6397.0588235294 286.5752262443) (10 6410.2531674208 279.1889140271) (10 6447.963800905 279.0356334842))
((0 . "LWPOLYLINE") (100 . "AcDbEntity") (8 . "PLANTS") (62 . 94) (370 . 13) (100 . "AcDbPolyline") (90 . 2) (70 . 0)
(43 . 0.0) (10 6398.9444570136 320.5118778281) (10 6397.0588235294 286.5752262443))
((0 . "LWPOLYLINE") (100 . "AcDbEntity") (8 . "PLANTS") (62 . 94) (370 . 13) (100 . "AcDbPolyline") (90 . 2) (70 . 0)
(43 . 0.0) (10 6398.9444570136 1070.8908371041) (10 6398.9444570136 1044.4937782805))
((0 . "LWPOLYLINE") (100 . "AcDbEntity") (8 . "PLANTS") (62 . 94) (370 . 13) (100 . "AcDbPolyline") (90 . 2) (70 . 0)
(43 . 0.0) (10 6417.7976244344 1089.7426470588) (10 6398.9444570136 1070.8908371041))
((0 . "LWPOLYLINE") (100 . "AcDbEntity") (8 . "PLANTS") (62 . 94) (370 . 13) (100 . "AcDbPolyline") (90 . 3) (70 . 0)
(43 . 0.0) (10 6461.1616515837 1042.6102941176) (10 6417.7976244344 1040.7302036199) (10 6398.9444570136
1044.4937782805))
((0 . "LWPOLYLINE") (100 . "AcDbEntity") (8 . "PLANTS") (62 . 94) (370 . 13) (100 . "AcDbPolyline") (90 . 2) (70 . 0)
(43 . 0.0) (10 6398.9444570136 320.5118778281) (10 6417.7976244344 324.2845022624))
((0 . "LWPOLYLINE") (100 . "AcDbEntity") (8 . "PLANTS") (62 . 94) (370 . 13) (100 . "AcDbPolyline") (90 . 3) (70 . 0)
(43 . 0.0) (10 6414.0271493213 3559.5779411765) (10 6399.0928733032 3582.2023755656) (10 6402.7149321267
3616.1390271493))
((0 . "LWPOLYLINE") (100 . "AcDbEntity") (8 . "PLANTS") (62 . 94) (370 . 13) (100 . "AcDbPolyline") (90 . 3) (70 . 0)
(43 . 0.0) (10 6402.7149321267 3616.1390271493) (10 6417.7914027149 3617.3430995475) (10 6430.9954751131
3633.1066742081))
((0 . "LWPOLYLINE") (100 . "AcDbEntity") (8 . "PLANTS") (62 . 94) (370 . 13) (100 . "AcDbPolyline") (90 . 3) (70 . 0)
(43 . 0.0) (10 6414.0271493213 3518.0995475113) (10 6407.6764705882 3522.0246606335) (10 6406.4854072398
3536.9535067873))
((0 . "LWPOLYLINE") (100 . "AcDbEntity") (8 . "PLANTS") (62 . 94) (370 . 13) (100 . "AcDbPolyline") (90 . 2) (70 . 0)
(43 . 0.0) (10 6429.109841629 3974.3593891403) (10 6414.0271493213 4053.5449095023))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6447.963800905 4185.520361991 0.0) (10 6436.2331922381 4185.4909390042 0.0) (10 6475.4676146352
4051.9048780025 0.0) (10 6414.0271493213 4053.5449095023 0.0))
((0 . "LWPOLYLINE") (100 . "AcDbEntity") (8 . "PLANTS") (62 . 94) (370 . 13) (100 . "AcDbPolyline") (90 . 3) (70 . 0)
(43 . 0.0) (10 6414.0271493213 3883.8616515837) (10 6444.1933257919 3884.917760181) (10 6474.3587104072
3906.4860859729))
((0 . "LWPOLYLINE") (100 . "AcDbEntity") (8 . "PLANTS") (62 . 94) (370 . 13) (100 . "AcDbPolyline") (90 . 2) (70 . 0)
(43 . 0.0) (10 6414.0271493213 1168.9281674208) (10 6421.5688914027 1138.7641402715))
((0 . "LWPOLYLINE") (100 . "AcDbEntity") (8 . "PLANTS") (62 . 94) (370 . 13) (100 . "AcDbPolyline") (90 . 2) (70 . 0)
(43 . 0.0) (10 6414.0271493213 1168.9281674208) (10 6417.7978506787 1184.0130090498))
((0 . "LWPOLYLINE") (100 . "AcDbEntity") (8 . "PLANTS") (62 . 94) (370 . 13) (100 . "AcDbPolyline") (90 . 2) (70 . 0)
(43 . 0.0) (10 6417.7976244344 3778.2805429864) (10 6432.8811085973 3785.8216063348))
((0 . "LWPOLYLINE") (100 . "AcDbEntity") (8 . "PLANTS") (62 . 94) (370 . 13) (100 . "AcDbPolyline") (90 . 2) (70 . 0)
(43 . 0.0) (10 6444.1933257919 1089.7426470588) (10 6417.7976244344 1089.7426470588))
((0 . "LWPOLYLINE") (100 . "AcDbEntity") (8 . "PLANTS") (62 . 94) (370 . 13) (100 . "AcDbPolyline") (90 . 2) (70 . 0)
(43 . 0.0) (10 6417.7976244344 1089.7426470588) (10 6421.5688914027 1138.7641402715))
((0 . "LWPOLYLINE") (100 . "AcDbEntity") (8 . "PLANTS") (62 . 94) (370 . 13) (100 . "AcDbPolyline") (90 . 2) (70 . 0)
(43 . 0.0) (10 6432.8811085973 509.0497737557) (10 6420.8923559259 531.6086308194))
((0 . "LWPOLYLINE") (100 . "AcDbEntity") (8 . "PLANTS") (62 . 94) (370 . 13) (100 . "AcDbPolyline") (90 . 2) (70 . 0)
(43 . 0.0) (10 6417.7976244344 346.9089366516) (10 6417.7976244344 324.2845022624))
((0 . "LWPOLYLINE") (100 . "AcDbEntity") (8 . "PLANTS") (62 . 94) (370 . 13) (100 . "AcDbPolyline") (90 . 2) (70 . 0)
(43 . 0.0) (10 6417.7976244344 346.9089366516) (10 6432.8811085973 365.7607466063))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6447.963800905 279.0356334842 0.0) (10 6453.506810556 298.484974363 0.0) (10 6439.3227042502
323.8968557932 0.0) (10 6417.7976244344 324.2845022624 0.0))
((0 . "LWPOLYLINE") (100 . "AcDbEntity") (8 . "PLANTS") (62 . 94) (370 . 13) (100 . "AcDbPolyline") (90 . 3) (70 . 0)
(43 . 0.0) (10 6417.7978506787 1235.2147535127) (10 6417.7978506787 1202.8648190045) (10 6417.7978506787
1184.0130090498))
((0 . "LWPOLYLINE") (100 . "AcDbEntity") (8 . "PLANTS") (62 . 94) (370 . 13) (100 . "AcDbPolyline") (90 . 2) (70 . 0)
(43 . 0.0) (10 6444.1933257919 1184.0130090498) (10 6417.7978506787 1184.0130090498))
((0 . "LWPOLYLINE") (100 . "AcDbEntity") (8 . "PLANTS") (62 . 94) (370 . 13) (100 . "AcDbPolyline") (90 . 2) (70 . 0)
(43 . 0.0) (10 6421.5688914027 3472.850678733) (10 6429.109841629 3487.9333710407))
((0 . "LWPOLYLINE") (100 . "AcDbEntity") (8 . "PLANTS") (62 . 94) (370 . 13) (100 . "AcDbPolyline") (90 . 2) (70 . 0)
(43 . 0.0) (10 6444.1933257919 1138.7641402715) (10 6421.5688914027 1138.7641402715))
((0 . "LWPOLYLINE") (100 . "AcDbEntity") (8 . "PLANTS") (62 . 94) (370 . 13) (100 . "AcDbPolyline") (90 . 3) (70 . 0)
(43 . 0.0) (10 6429.109841629 3974.3593891403) (10 6436.5038461538 3955.5048642534) (10 6436.6515837104
3940.4227375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6493.2126696833 3676.4705882353 0.0) (10 6464.6408457424 3661.1325526137 0.0) (10 6418.6640080152
3687.9314903779 0.0) (10 6429.109841629 3721.7194570136 0.0))
((0 . "LWPOLYLINE") (100 . "AcDbEntity") (8 . "PLANTS") (62 . 94) (370 . 13) (100 . "AcDbPolyline") (90 . 3) (70 . 0)
(43 . 0.0) (10 6429.109841629 3721.7194570136) (10 6443.8245475113 3726.6813348416) (10 6444.1933257919
3733.0316742081))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4591517713) (40
. 1) (40 . 1) (40 . 1) (40 . 1) (10 6466.8177601811 361.9909502263 0.0) (10 6466.8035206011 380.4631680138 0.0) (10
6453.9540018269 418.4689387037 0.0) (10 6440.3637163164 456.5851750218 0.0) (10 6429.109841629 475.113122172 0.0))
((0 . "LWPOLYLINE") (100 . "AcDbEntity") (8 . "PLANTS") (62 . 94) (370 . 13) (100 . "AcDbPolyline") (90 . 2) (70 . 0)
(43 . 0.0) (10 6430.9954751131 3633.1066742081) (10 6470.5882352941 3623.6806561086))
((0 . "LWPOLYLINE") (100 . "AcDbEntity") (8 . "PLANTS") (62 . 94) (370 . 13) (100 . "AcDbPolyline") (90 . 2) (70 . 0)
(43 . 0.0) (10 6444.1933257919 3657.6173076923) (10 6430.9954751131 3633.1066742081))
((0 . "LWPOLYLINE") (100 . "AcDbEntity") (8 . "PLANTS") (62 . 94) (370 . 13) (100 . "AcDbPolyline") (90 . 2) (70 . 0)
(43 . 0.0) (10 6466.817760181 361.9909502262) (10 6432.8811085973 365.7607466063))
((0 . "LWPOLYLINE") (100 . "AcDbEntity") (8 . "PLANTS") (62 . 94) (370 . 13) (100 . "AcDbPolyline") (90 . 3) (70 . 0)
(43 . 0.0) (10 6474.3587104072 3917.7983031674) (10 6463.0464932127 3928.0538461538) (10 6436.6515837104
3940.4227375566))
((0 . "LWPOLYLINE") (100 . "AcDbEntity") (8 . "PLANTS") (62 . 94) (370 . 13) (100 . "AcDbPolyline") (90 . 2) (70 . 0)
(43 . 0.0) (10 6440.4220588235 3503.0168552036) (10 6436.6515837104 3510.5578054299))
((0 . "LWPOLYLINE") (100 . "AcDbEntity") (8 . "PLANTS") (62 . 94) (370 . 13) (100 . "AcDbPolyline") (90 . 3) (70 . 0)
(43 . 0.0) (10 6459.2760180995 1187.7828054299) (10 6455.5055429864 1184.0130090498) (10 6444.1933257919
1184.0130090498))
((0 . "LWPOLYLINE") (100 . "AcDbEntity") (8 . "PLANTS") (62 . 94) (370 . 13) (100 . "AcDbPolyline") (90 . 2) (70 . 0)
(43 . 0.0) (10 6444.1933257919 1184.0130090498) (10 6447.963800905 1146.3037330317))
((0 . "LWPOLYLINE") (100 . "AcDbEntity") (8 . "PLANTS") (62 . 94) (370 . 13) (100 . "AcDbPolyline") (90 . 2) (70 . 0)
(43 . 0.0) (10 6444.1933257919 1184.0130090498) (10 6444.3149319768 1221.2583949348))
((0 . "LWPOLYLINE") (100 . "AcDbEntity") (8 . "PLANTS") (62 . 94) (370 . 13) (100 . "AcDbPolyline") (90 . 2) (70 . 0)
(43 . 0.0) (10 6444.1933257919 1138.7641402715) (10 6451.7342760181 1104.8274886878))
((0 . "LWPOLYLINE") (100 . "AcDbEntity") (8 . "PLANTS") (62 . 94) (370 . 13) (100 . "AcDbPolyline") (90 . 2) (70 . 0)
(43 . 0.0) (10 6444.1933257919 1138.7641402715) (10 6447.963800905 1146.3037330317))
((0 . "LWPOLYLINE") (100 . "AcDbEntity") (8 . "PLANTS") (62 . 94) (370 . 13) (100 . "AcDbPolyline") (90 . 3) (70 . 0)
(43 . 0.0) (10 6461.1616515837 1042.6102941176) (10 6445.2496606335 1063.3484162896) (10 6444.1933257919
1089.7426470588))
((0 . "LWPOLYLINE") (100 . "AcDbEntity") (8 . "PLANTS") (62 . 94) (370 . 13) (100 . "AcDbPolyline") (90 . 2) (70 . 0)
(43 . 0.0) (10 6444.1933257919 1089.7426470588) (10 6451.7342760181 1104.8274886878))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6447.963800905 4185.5203619909 0.0) (10 6469.512775716 4243.7086744003 0.0) (10 6405.3371391243
4308.5704115413 0.0) (10 6447.9700226244 4366.5002828054 0.0))
((0 . "LWPOLYLINE") (100 . "AcDbEntity") (8 . "PLANTS") (62 . 94) (370 . 13) (100 . "AcDbPolyline") (90 . 2) (70 . 0)
(43 . 0.0) (10 6455.5055429864 1150.0763574661) (10 6447.963800905 1146.3037330317))
((0 . "LWPOLYLINE") (100 . "AcDbEntity") (8 . "PLANTS") (62 . 94) (370 . 13) (100 . "AcDbPolyline") (90 . 2) (70 . 0)
(43 . 0.0) (10 6447.963800905 965.3082579186) (10 6451.7342760181 942.6838235294))
((0 . "LWPOLYLINE") (100 . "AcDbEntity") (8 . "PLANTS") (62 . 94) (370 . 13) (100 . "AcDbPolyline") (90 . 2) (70 . 0)
(43 . 0.0) (10 6455.5055429864 972.850678733) (10 6447.963800905 965.3082579186))
((0 . "LWPOLYLINE") (100 . "AcDbEntity") (8 . "PLANTS") (62 . 94) (370 . 13) (100 . "AcDbPolyline") (90 . 3) (70 . 0)
(43 . 0.0) (10 6470.5882352941 260.1809954751) (10 6459.2760180995 275.1097285068) (10 6447.963800905 279.0356334842))
((0 . "LWPOLYLINE") (100 . "AcDbEntity") (8 . "PLANTS") (62 . 94) (370 . 13) (100 . "AcDbPolyline") (90 . 2) (70 . 0)
(43 . 0.0) (10 6496.9833710407 1172.7007918552) (10 6494.7858208451 1194.6947692147))
((0 . "LWPOLYLINE") (100 . "AcDbEntity") (8 . "PLANTS") (62 . 94) (370 . 13) (100 . "AcDbPolyline") (90 . 2) (70 . 0)
(43 . 0.0) (10 6451.7342760181 1104.8274886878) (10 6481.9004524887 1104.8274886878))
((0 . "LWPOLYLINE") (100 . "AcDbEntity") (8 . "PLANTS") (62 . 94) (370 . 13) (100 . "AcDbPolyline") (90 . 2) (70 . 0)
(43 . 0.0) (10 6493.2126696833 931.3716063348) (10 6451.7342760181 942.6838235294))
((0 . "LWPOLYLINE") (100 . "AcDbEntity") (8 . "PLANTS") (62 . 94) (370 . 13) (100 . "AcDbPolyline") (90 . 2) (70 . 0)
(43 . 0.0) (10 6451.7342760181 904.9773755656) (10 6451.7342760181 942.6838235294))
((0 . "LWPOLYLINE") (100 . "AcDbEntity") (8 . "PLANTS") (62 . 94) (370 . 13) (100 . "AcDbPolyline") (90 . 3) (70 . 0)
(43 . 0.0) (10 6496.9831447964 916.2895927602) (10 6481.9004524887 905.1320135747) (10 6451.7342760181 904.9773755656))
((0 . "LWPOLYLINE") (100 . "AcDbEntity") (8 . "PLANTS") (62 . 94) (370 . 13) (100 . "AcDbPolyline") (90 . 2) (70 . 0)
(43 . 0.0) (10 6455.5055429864 972.850678733) (10 6496.9831447964 972.850678733))
((0 . "LWPOLYLINE") (100 . "AcDbEntity") (8 . "PLANTS") (62 . 94) (370 . 13) (100 . "AcDbPolyline") (90 . 3) (70 . 0)
(43 . 0.0) (10 6455.5055429864 972.850678733) (10 6455.653280543 999.2449095023) (10 6463.0464932127 1029.4117647059))
((0 . "LWPOLYLINE") (100 . "AcDbEntity") (8 . "PLANTS") (62 . 94) (370 . 13) (100 . "AcDbPolyline") (90 . 2) (70 . 0)
(43 . 0.0) (10 6461.1616515837 1042.6102941176) (10 6463.0464932127 1029.4117647059))
((0 . "LWPOLYLINE") (100 . "AcDbEntity") (8 . "PLANTS") (62 . 94) (370 . 13) (100 . "AcDbPolyline") (90 . 2) (70 . 0)
(43 . 0.0) (10 6461.1616515837 1042.6102941176) (10 6481.9004524887 1085.9728506787))
((0 . "LWPOLYLINE") (100 . "AcDbEntity") (8 . "PLANTS") (62 . 94) (370 . 13) (100 . "AcDbPolyline") (90 . 2) (70 . 0)
(43 . 0.0) (10 6461.1616515837 1042.6102941176) (10 6500.7544117647 1048.2664027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6493.2126696832 3676.4705882353 0.0) (10 6506.3541173812 3697.6074707585 0.0) (10 6493.0266163095
3731.3805613763 0.0) (10 6463.0464932127 3717.9483031674 0.0))
((0 . "LWPOLYLINE") (100 . "AcDbEntity") (8 . "PLANTS") (62 . 94) (370 . 13) (100 . "AcDbPolyline") (90 . 3) (70 . 0)
(43 . 0.0) (10 6496.9831447964 1014.3297511312) (10 6481.9004524887 1015.5331447964) (10 6463.0464932127
1029.4117647059))
((0 . "LWPOLYLINE") (100 . "AcDbEntity") (8 . "PLANTS") (62 . 94) (370 . 13) (100 . "AcDbPolyline") (90 . 2) (70 . 0)
(43 . 0.0) (10 6466.817760181 3789.592760181) (10 6474.3587104072 3782.0516968326))
((0 . "LWPOLYLINE") (100 . "AcDbEntity") (8 . "PLANTS") (62 . 94) (370 . 13) (100 . "AcDbPolyline") (90 . 3) (70 . 0)
(43 . 0.0) (10 6466.817760181 3755.6561085973) (10 6474.3587104072 3763.1971719457) (10 6474.3587104072 3770.739479638))
((0 . "LWPOLYLINE") (100 . "AcDbEntity") (8 . "PLANTS") (62 . 94) (370 . 13) (100 . "AcDbPolyline") (90 . 3) (70 . 0)
(43 . 0.0) (10 6466.817760181 361.9909502262) (10 6475.415158371 316.742081448) (10 6489.4421945701 297.8874434389))
((0 . "LWPOLYLINE") (100 . "AcDbEntity") (8 . "PLANTS") (62 . 94) (370 . 13) (100 . "AcDbPolyline") (90 . 2) (70 . 0)
(43 . 0.0) (10 6470.5882352941 3616.1390271493) (10 6470.5882352941 3623.6806561086))
((0 . "LWPOLYLINE") (100 . "AcDbEntity") (8 . "PLANTS") (62 . 94) (370 . 13) (100 . "AcDbPolyline") (90 . 2) (70 . 0)
(43 . 0.0) (10 6493.2126696833 3634.9928733032) (10 6470.5882352941 3623.6806561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6519.6075791855 384.6153846154 0.0) (10 6487.4756010336 406.8837331095 0.0) (10 6514.1065447158
471.7176898244 0.0) (10 6470.5882352941 478.8829185522 0.0))
((0 . "LWPOLYLINE") (100 . "AcDbEntity") (8 . "PLANTS") (62 . 94) (370 . 13) (100 . "AcDbPolyline") (90 . 2) (70 . 0)
(43 . 0.0) (10 6470.5882352941 260.1809954751) (10 6485.6709276018 260.1809954751))
((0 . "LWPOLYLINE") (100 . "AcDbEntity") (8 . "PLANTS") (62 . 94) (370 . 13) (100 . "AcDbPolyline") (90 . 2) (70 . 0)
(43 . 0.0) (10 6474.3587104072 3917.7983031674) (10 6474.3587104072 3906.4860859729))
((0 . "LWPOLYLINE") (100 . "AcDbEntity") (8 . "PLANTS") (62 . 94) (370 . 13) (100 . "AcDbPolyline") (90 . 3) (70 . 0)
(43 . 0.0) (10 6474.3587104072 3917.7983031674) (10 6489.2875565611 3929.110520362) (10 6496.9831447964
3944.1926470588))
((0 . "LWPOLYLINE") (100 . "AcDbEntity") (8 . "PLANTS") (62 . 94) (370 . 13) (100 . "AcDbPolyline") (90 . 3) (70 . 0)
(43 . 0.0) (10 6481.9004524887 3842.3826923077) (10 6481.7458144796 3895.1731900452) (10 6474.3587104072
3906.4860859729))
((0 . "LWPOLYLINE") (100 . "AcDbEntity") (8 . "PLANTS") (62 . 94) (370 . 13) (100 . "AcDbPolyline") (90 . 2) (70 . 0)
(43 . 0.0) (10 6478.1299773756 1168.9281674208) (10 6496.9833710407 1172.7007918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6553.5442307692 3812.2171945701 0.0) (10 6527.1346288111 3808.0786179579 0.0) (10 6494.9420794954
3816.9236077202 0.0) (10 6481.9004524887 3842.3826923077 0.0))
((0 . "LWPOLYLINE") (100 . "AcDbEntity") (8 . "PLANTS") (62 . 94) (370 . 13) (100 . "AcDbPolyline") (90 . 2) (70 . 0)
(43 . 0.0) (10 6481.9004524887 1104.8274886878) (10 6481.9004524887 1085.9728506787))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6496.9833710407 1150.0763574661 0.0) (10 6506.5364636375 1130.1534079123 0.0) (10 6477.1341143775
1123.7697200449 0.0) (10 6481.9004524887 1104.8274886878 0.0))
((0 . "LWPOLYLINE") (100 . "AcDbEntity") (8 . "PLANTS") (62 . 94) (370 . 13) (100 . "AcDbPolyline") (90 . 3) (70 . 0)
(43 . 0.0) (10 6508.295361991 1059.5786199095) (10 6504.3702488688 1078.2771493213) (10 6481.9004524887
1085.9728506787))
((0 . "LWPOLYLINE") (100 . "AcDbEntity") (8 . "PLANTS") (62 . 94) (370 . 13) (100 . "AcDbPolyline") (90 . 2) (70 . 0)
(43 . 0.0) (10 6508.295361991 256.411199095) (10 6485.6709276018 260.1809954751))
((0 . "LWPOLYLINE") (100 . "AcDbEntity") (8 . "PLANTS") (62 . 94) (370 . 13) (100 . "AcDbPolyline") (90 . 2) (70 . 0)
(43 . 0.0) (10 6489.4421945701 297.8874434389) (10 6485.6709276018 260.1809954751))
((0 . "LWPOLYLINE") (100 . "AcDbEntity") (8 . "PLANTS") (62 . 94) (370 . 13) (100 . "AcDbPolyline") (90 . 3) (70 . 0)
(43 . 0.0) (10 6489.4421945701 4008.296040724) (10 6489.5968325792 3955.5055429864) (10 6496.9831447964
3944.1926470588))
((0 . "LWPOLYLINE") (100 . "AcDbEntity") (8 . "PLANTS") (62 . 94) (370 . 13) (100 . "AcDbPolyline") (90 . 3) (70 . 0)
(43 . 0.0) (10 6506.0334841629 4090.4978506787) (10 6489.5968325792 4076.1624434389) (10 6489.4421945701
4008.296040724))
((0 . "LWPOLYLINE") (100 . "AcDbEntity") (8 . "PLANTS") (62 . 94) (370 . 13) (100 . "AcDbPolyline") (90 . 2) (70 . 0)
(43 . 0.0) (10 6504.5248868778 4012.0659502262) (10 6489.4421945701 4008.296040724))
((0 . "LWPOLYLINE") (100 . "AcDbEntity") (8 . "PLANTS") (62 . 94) (370 . 13) (100 . "AcDbPolyline") (90 . 3) (70 . 0)
(43 . 0.0) (10 6489.4421945701 297.8874434389) (10 6500.6058823529 305.4367647059) (10 6512.0666289593 324.2845022624))
((0 . "LWPOLYLINE") (100 . "AcDbEntity") (8 . "PLANTS") (62 . 94) (370 . 13) (100 . "AcDbPolyline") (90 . 2) (70 . 0)
(43 . 0.0) (10 6493.2126696833 4234.5403846154) (10 6496.1131944628 4246.1423532096))
((0 . "LWPOLYLINE") (100 . "AcDbEntity") (8 . "PLANTS") (62 . 94) (370 . 13) (100 . "AcDbPolyline") (90 . 2) (70 . 0)
(43 . 0.0) (10 6493.2126696833 3676.4705882353) (10 6504.5248868778 3661.3872171946))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4387007634) (40
. 1) (40 . 1) (40 . 1) (40 . 1) (10 6504.5248868778 3661.3872171946 0.0) (10 6523.2691605413 3676.7036388607 0.0) (10
6560.076608026 3637.3292346374 0.0) (10 6509.1710807797 3617.1686554761 0.0) (10 6493.2126696832 3634.9928733032 0.0))
((0 . "LWPOLYLINE") (100 . "AcDbEntity") (8 . "PLANTS") (62 . 94) (370 . 13) (100 . "AcDbPolyline") (90 . 2) (70 . 0)
(43 . 0.0) (10 6504.5248868778 3661.3872171946) (10 6493.2126696833 3634.9928733032))
((0 . "LWPOLYLINE") (100 . "AcDbEntity") (8 . "PLANTS") (62 . 94) (370 . 13) (100 . "AcDbPolyline") (90 . 2) (70 . 0)
(43 . 0.0) (10 6496.9831447964 916.2895927602) (10 6493.2126696833 931.3716063348))
((0 . "LWPOLYLINE") (100 . "AcDbEntity") (8 . "PLANTS") (62 . 94) (370 . 13) (100 . "AcDbPolyline") (90 . 2) (70 . 0)
(43 . 0.0) (10 6493.2126696833 931.3716063348) (10 6496.9831447964 972.850678733))
((0 . "LWPOLYLINE") (100 . "AcDbEntity") (8 . "PLANTS") (62 . 94) (370 . 13) (100 . "AcDbPolyline") (90 . 2) (70 . 0)
(43 . 0.0) (10 6519.6075791855 3947.963800905) (10 6496.9831447964 3944.1926470588))
((0 . "LWPOLYLINE") (100 . "AcDbEntity") (8 . "PLANTS") (62 . 94) (370 . 13) (100 . "AcDbPolyline") (90 . 2) (70 . 0)
(43 . 0.0) (10 6496.9831447964 1014.3297511312) (10 6496.9831447964 972.850678733))
((0 . "LWPOLYLINE") (100 . "AcDbEntity") (8 . "PLANTS") (62 . 94) (370 . 13) (100 . "AcDbPolyline") (90 . 2) (70 . 0)
(43 . 0.0) (10 6496.9831447964 1014.3297511312) (10 6515.8371040724 1025.6419683258))
((0 . "LWPOLYLINE") (100 . "AcDbEntity") (8 . "PLANTS") (62 . 94) (370 . 13) (100 . "AcDbPolyline") (90 . 2) (70 . 0)
(43 . 0.0) (10 6496.9831447964 916.2895927602) (10 6512.0666289593 916.2895927602))
((0 . "LWPOLYLINE") (100 . "AcDbEntity") (8 . "PLANTS") (62 . 94) (370 . 13) (100 . "AcDbPolyline") (90 . 2) (70 . 0)
(43 . 0.0) (10 6496.9833710407 1150.0763574661) (10 6496.9833710407 1172.7007918552))
((0 . "LWPOLYLINE") (100 . "AcDbEntity") (8 . "PLANTS") (62 . 94) (370 . 13) (100 . "AcDbPolyline") (90 . 2) (70 . 0)
(43 . 0.0) (10 6496.9833710407 1150.0763574661) (10 6546.003280543 1157.6159502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6506.0334841629 4090.4978506787 0.0) (10 6480.4385978583 4109.9364896329 0.0) (10 6515.0107976185
4142.1788329085 0.0) (10 6500.7544117647 4166.667081448 0.0))
((0 . "LWPOLYLINE") (100 . "AcDbEntity") (8 . "PLANTS") (62 . 94) (370 . 13) (100 . "AcDbPolyline") (90 . 2) (70 . 0)
(43 . 0.0) (10 6515.8371040724 1025.6419683258) (10 6500.7544117647 1048.2664027149))
((0 . "LWPOLYLINE") (100 . "AcDbEntity") (8 . "PLANTS") (62 . 94) (370 . 13) (100 . "AcDbPolyline") (90 . 2) (70 . 0)
(43 . 0.0) (10 6508.295361991 1059.5786199095) (10 6500.7544117647 1048.2664027149))
((0 . "LWPOLYLINE") (100 . "AcDbEntity") (8 . "PLANTS") (62 . 94) (370 . 13) (100 . "AcDbPolyline") (90 . 3) (70 . 0)
(43 . 0.0) (10 6506.0334841629 4090.4978506787) (10 6512.0666289593 4083.7104072398) (10 6523.3788461538
4083.7104072398))
((0 . "SPLINE") (100 . "AcDbEntity") (8 . "PLANTS") (62 . 94) (370 . 13) (100 . "AcDbSpline") (70 . 3) (71 . 3) (72 .
10) (73 . 6) (74 . 0) (42 . 0.0000001) (43 . 0.0000001) (40 . -1) (40 . -0.5995632109) (40 . -0.3511959223) (40 . 0.0)
(40 . 0.4004367891) (40 . 0.6488040777) (40 . 1) (40 . 1.4004367891) (40 . 1.6488040777) (40 . 2) (10 6511.6581455523
4096.1210779114 0.0) (10 6503.2301387927 4086.2750447952 0.0) (10 6509.3568382279 4099.2084789305 0.0) (10
6511.6581455523 4096.1210779114 0.0) (10 6503.2301387927 4086.2750447952 0.0) (10 6509.3568382279 4099.2084789305 0.0))
((0 . "LWPOLYLINE") (100 . "AcDbEntity") (8 . "PLANTS") (62 . 94) (370 . 13) (100 . "AcDbPolyline") (90 . 2) (70 . 0)
(43 . 0.0) (10 6538.4615384615 1052.036199095) (10 6508.295361991 1059.5786199095))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5464767929) (40
. 1) (40 . 1) (40 . 1) (40 . 1) (10 6508.2953619909 256.411199095 0.0) (10 6527.1301375661 228.9260757602 0.0) (10
6583.2296155913 249.510356105 0.0) (10 6635.7136816206 227.6332423191 0.0) (10 6651.5837104073 252.6385746606 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6508.295361991 256.411199095 0.0) (10 6539.5481129945 310.5290222151 0.0) (10 6621.6100015364
302.32236048 0.0) (10 6651.5837104072 252.6385746606 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6583.7104072398 904.9773755656 0.0) (10 6560.3451826704 895.7734020498 0.0) (10 6529.5758501135
894.9406894543 0.0) (10 6512.0666289593 916.2895927602 0.0))
((0 . "LWPOLYLINE") (100 . "AcDbEntity") (8 . "PLANTS") (62 . 94) (370 . 13) (100 . "AcDbPolyline") (90 . 3) (70 . 0)
(43 . 0.0) (10 6534.6910633484 938.9140271493) (10 6523.3788461538 931.3667420814) (10 6512.0666289593 916.2895927602))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6553.5442307692 343.1363122172 0.0) (10 6548.6388485375 327.0883630357 0.0) (10 6527.1495650056
315.8819145501 0.0) (10 6512.0666289593 324.2845022624 0.0))
((0 . "LWPOLYLINE") (100 . "AcDbEntity") (8 . "PLANTS") (62 . 94) (370 . 13) (100 . "AcDbPolyline") (90 . 3) (70 . 0)
(43 . 0.0) (10 6519.6075791855 358.2211538462) (10 6515.984841629 354.2952488688) (10 6512.0666289593 324.2845022624))
((0 . "LWPOLYLINE") (100 . "AcDbEntity") (8 . "PLANTS") (62 . 94) (370 . 13) (100 . "AcDbPolyline") (90 . 2) (70 . 0)
(43 . 0.0) (10 6538.4615384615 1023.7556561086) (10 6515.8371040724 1025.6419683258))
((0 . "LWPOLYLINE") (100 . "AcDbEntity") (8 . "PLANTS") (62 . 94) (370 . 13) (100 . "AcDbPolyline") (90 . 2) (70 . 0)
(43 . 0.0) (10 6515.8371040724 482.6555429864) (10 6527.149321267 467.5707013575))
((0 . "LWPOLYLINE") (100 . "AcDbEntity") (8 . "PLANTS") (62 . 94) (370 . 13) (100 . "AcDbPolyline") (90 . 3) (70 . 0)
(43 . 0.0) (10 6533.1838957487 4153.4655999948) (10 6527.2970588235 4128.9592760181) (10 6523.3788461538
4083.7104072398))
((0 . "LWPOLYLINE") (100 . "AcDbEntity") (8 . "PLANTS") (62 . 94) (370 . 13) (100 . "AcDbPolyline") (90 . 3) (70 . 0)
(43 . 0.0) (10 6519.6075791855 3947.963800905) (10 6527.1562217195 3936.6578054299) (10 6546.003280543 3921.5682126697))
((0 . "LWPOLYLINE") (100 . "AcDbEntity") (8 . "PLANTS") (62 . 94) (370 . 13) (100 . "AcDbPolyline") (90 . 3) (70 . 0)
(43 . 0.0) (10 6546.003280543 3985.6716063348) (10 6541.0341628959 3970.7363122172) (10 6519.6075791855 3947.963800905))
((0 . "LWPOLYLINE") (100 . "AcDbEntity") (8 . "PLANTS") (62 . 94) (370 . 13) (100 . "AcDbPolyline") (90 . 2) (70 . 0)
(43 . 0.0) (10 6519.6075791855 384.6153846154) (10 6519.6075791855 358.2211538462))
((0 . "LWPOLYLINE") (100 . "AcDbEntity") (8 . "PLANTS") (62 . 94) (370 . 13) (100 . "AcDbPolyline") (90 . 2) (70 . 0)
(43 . 0.0) (10 6519.6075791855 384.6153846154) (10 6542.2320135747 403.4700226244))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6553.5442307692 343.1363122172 0.0) (10 6546.1539541404 357.120950712 0.0) (10 6526.9982682212
344.2368274287 0.0) (10 6519.6075791855 358.2211538462 0.0))
((0 . "LWPOLYLINE") (100 . "AcDbEntity") (8 . "PLANTS") (62 . 94) (370 . 13) (100 . "AcDbPolyline") (90 . 3) (70 . 0)
(43 . 0.0) (10 6527.149321267 4049.7737556561) (10 6529.5742081448 4076.1624434389) (10 6523.3788461538
4083.7104072398))
((0 . "LWPOLYLINE") (100 . "AcDbEntity") (8 . "PLANTS") (62 . 94) (370 . 13) (100 . "AcDbPolyline") (90 . 2) (70 . 0)
(43 . 0.0) (10 6534.6910633484 938.9140271493) (10 6572.3981900452 938.9140271493))
((0 . "LWPOLYLINE") (100 . "AcDbEntity") (8 . "PLANTS") (62 . 94) (370 . 13) (100 . "AcDbPolyline") (90 . 3) (70 . 0)
(43 . 0.0) (10 6534.6910633484 938.9140271493) (10 6534.8457013575 965.3082579186) (10 6542.2320135747 976.6204751131))
((0 . "LWPOLYLINE") (100 . "AcDbEntity") (8 . "PLANTS") (62 . 94) (370 . 13) (100 . "AcDbPolyline") (90 . 2) (70 . 0)
(43 . 0.0) (10 6538.4615384615 1052.036199095) (10 6538.4615384615 1023.7556561086))
((0 . "LWPOLYLINE") (100 . "AcDbEntity") (8 . "PLANTS") (62 . 94) (370 . 13) (100 . "AcDbPolyline") (90 . 2) (70 . 0)
(43 . 0.0) (10 6538.4615384615 1052.036199095) (10 6546.003280543 1055.8059954751))
((0 . "LWPOLYLINE") (100 . "AcDbEntity") (8 . "PLANTS") (62 . 94) (370 . 13) (100 . "AcDbPolyline") (90 . 3) (70 . 0)
(43 . 0.0) (10 6606.334841629 1003.0175339367) (10 6587.4808823529 1004.0662895928) (10 6538.4615384615
1023.7556561086))
((0 . "LWPOLYLINE") (100 . "AcDbEntity") (8 . "PLANTS") (62 . 94) (370 . 13) (100 . "AcDbPolyline") (90 . 3) (70 . 0)
(43 . 0.0) (10 6542.2320135747 976.6204751131) (10 6538.6092760181 987.9326923077) (10 6538.4615384615 1023.7556561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6542.2320135747 976.6204751131 0.0) (10 6572.7328304917 989.2061075199 0.0) (10 6581.480035141
956.4636534555 0.0) (10 6572.3981900452 938.9140271493 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6542.2320135747 403.4700226244 0.0) (10 6541.1610164697 440.094716205 0.0) (10 6586.8168474199
463.6279252361 0.0) (10 6572.3981900452 501.5073529412 0.0))
((0 . "LWPOLYLINE") (100 . "AcDbEntity") (8 . "PLANTS") (62 . 94) (370 . 13) (100 . "AcDbPolyline") (90 . 3) (70 . 0)
(43 . 0.0) (10 6542.2320135747 403.4700226244) (10 6564.8502262443 403.617081448) (10 6572.3981900452 407.2398190045))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6572.4785845947 6730.7692307692 0.0) (10 6550.6595321593 6733.0650682715 0.0) (10 6546.9705883407
6759.7238952358 0.0) (10 6546.003280543 6776.0180995475 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.6368690872)
(40 . 0.8461466809) (40 . 1) (40 . 1) (40 . 1) (40 . 1) (10 6636.5010180995 6832.5791855203 0.0) (10 6598.4204002905
6820.9640410675 0.0) (10 6490.3986069509 6873.243166272 0.0) (10 6500.3773113703 6773.0743975468 0.0) (10
6533.4921726193 6770.1459446641 0.0) (10 6546.003280543 6776.0180995475 0.0))
((0 . "LWPOLYLINE") (100 . "AcDbEntity") (8 . "PLANTS") (62 . 94) (370 . 13) (100 . "AcDbPolyline") (90 . 3) (70 . 0)
(43 . 0.0) (10 6610.1053167421 6779.7885746606) (10 6583.7104072398 6783.4115384615) (10 6546.003280543
6776.0180995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6546.003280543 3985.6716063348 0.0) (10 6531.5897957993 4009.1612338775 0.0) (10 6563.4592280777
4037.7866993025 0.0) (10 6576.1686651584 4049.7737556561 0.0))
((0 . "LWPOLYLINE") (100 . "AcDbEntity") (8 . "PLANTS") (62 . 94) (370 . 13) (100 . "AcDbPolyline") (90 . 3) (70 . 0)
(43 . 0.0) (10 6546.003280543 3985.6716063348) (10 6564.8564479638 3993.3673076923) (10 6591.2521493213
4023.3781674208))
((0 . "LWPOLYLINE") (100 . "AcDbEntity") (8 . "PLANTS") (62 . 94) (370 . 13) (100 . "AcDbPolyline") (90 . 3) (70 . 0)
(43 . 0.0) (10 6564.8564479638 3865.0071266968) (10 6539.6726244344 3891.4027149321) (10 6546.003280543
3921.5682126697))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5248166498) (40
. 1) (40 . 1) (40 . 1) (40 . 1) (10 6659.1254524887 3996.9838235294 0.0) (10 6626.8965294369 4006.6648588629 0.0) (10
6604.8780958556 3960.5891774226 0.0) (10 6571.9561018334 3923.0826106598 0.0) (10 6546.0032805429 3921.5682126698 0.0))
((0 . "LWPOLYLINE") (100 . "AcDbEntity") (8 . "PLANTS") (62 . 94) (370 . 13) (100 . "AcDbPolyline") (90 . 2) (70 . 0)
(43 . 0.0) (10 6546.003280543 1157.6159502262) (10 6549.7737556561 1131.221719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6620.497118553 1098.8759498373 0.0) (10 6603.4318023465 1079.5810999599 0.0) (10 6578.6592741384
1042.440055181 0.0) (10 6546.003280543 1055.8059954751 0.0))
((0 . "LWPOLYLINE") (100 . "AcDbEntity") (8 . "PLANTS") (62 . 94) (370 . 13) (100 . "AcDbPolyline") (90 . 2) (70 . 0)
(43 . 0.0) (10 6549.7737556561 1093.5152714932) (10 6546.003280543 1055.8059954751))
((0 . "LWPOLYLINE") (100 . "AcDbEntity") (8 . "PLANTS") (62 . 94) (370 . 13) (100 . "AcDbPolyline") (90 . 2) (70 . 0)
(43 . 0.0) (10 6549.7737556561 1093.5152714932) (10 6549.7737556561 1131.221719457))
((0 . "LWPOLYLINE") (100 . "AcDbEntity") (8 . "PLANTS") (62 . 94) (370 . 13) (100 . "AcDbPolyline") (90 . 3) (70 . 0)
(43 . 0.0) (10 6576.8287225996 1148.7826880697) (10 6568.4791855204 1136.190158371) (10 6549.7737556561 1131.221719457))
((0 . "LWPOLYLINE") (100 . "AcDbEntity") (8 . "PLANTS") (62 . 94) (370 . 13) (100 . "AcDbPolyline") (90 . 3) (70 . 0)
(43 . 0.0) (10 6549.7737556561 1093.5152714932) (10 6568.6277149321 1093.6685520362) (10 6579.9399321267
1101.0548642534))
((0 . "LWPOLYLINE") (100 . "AcDbEntity") (8 . "PLANTS") (62 . 94) (370 . 13) (100 . "AcDbPolyline") (90 . 3) (70 . 0)
(43 . 0.0) (10 6553.5442307692 3812.2171945701) (10 6561.0928733032 3802.1091628959) (10 6591.2521493213
3800.9049773756))
((0 . "LWPOLYLINE") (100 . "AcDbEntity") (8 . "PLANTS") (62 . 94) (370 . 13) (100 . "AcDbPolyline") (90 . 3) (70 . 0)
(43 . 0.0) (10 6564.8564479638 3865.0071266968) (10 6553.6919683258 3831.0704751131) (10 6553.5442307692
3812.2171945701))
((0 . "LWPOLYLINE") (100 . "AcDbEntity") (8 . "PLANTS") (62 . 94) (370 . 13) (100 . "AcDbPolyline") (90 . 3) (70 . 0)
(43 . 0.0) (10 6628.9064743095 3729.2565088637) (10 6568.6277149321 3729.2542986425) (10 6553.5442307692
3725.4906108597))
((0 . "LWPOLYLINE") (100 . "AcDbEntity") (8 . "PLANTS") (62 . 94) (370 . 13) (100 . "AcDbPolyline") (90 . 2) (70 . 0)
(43 . 0.0) (10 6553.5442307692 343.1363122172) (10 6561.0859728507 343.1363122172))
((0 . "LWPOLYLINE") (100 . "AcDbEntity") (8 . "PLANTS") (62 . 94) (370 . 13) (100 . "AcDbPolyline") (90 . 3) (70 . 0)
(43 . 0.0) (10 6602.5643665158 343.1363122172) (10 6568.6339366516 336.8001131222) (10 6561.0859728507 343.1363122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6561.0859728507 343.1363122172 0.0) (10 6555.6723484211 362.1198783157 0.0) (10 6594.7978512738
386.0760373867 0.0) (10 6602.5643665158 361.9909502262 0.0))
((0 . "LWPOLYLINE") (100 . "AcDbEntity") (8 . "PLANTS") (62 . 94) (370 . 13) (100 . "AcDbPolyline") (90 . 2) (70 . 0)
(43 . 0.0) (10 6576.1686651584 3868.778280543) (10 6564.8564479638 3865.0071266968))
((0 . "LWPOLYLINE") (100 . "AcDbEntity") (8 . "PLANTS") (62 . 94) (370 . 13) (100 . "AcDbPolyline") (90 . 3) (70 . 0)
(43 . 0.0) (10 6572.3981900452 938.9140271493) (10 6576.1686651584 931.3716063348) (10 6583.7104072398 927.6018099548))
((0 . "LWPOLYLINE") (100 . "AcDbEntity") (8 . "PLANTS") (62 . 94) (370 . 13) (100 . "AcDbPolyline") (90 . 2) (70 . 0)
(43 . 0.0) (10 6576.1686651584 4049.7737556561) (10 6583.7104072398 4049.7737556561))
((0 . "LWPOLYLINE") (100 . "AcDbEntity") (8 . "PLANTS") (62 . 94) (370 . 13) (100 . "AcDbPolyline") (90 . 3) (70 . 0)
(43 . 0.0) (10 6591.2521493213 4128.9592760181) (10 6572.5459276018 4072.3981900452) (10 6576.1686651584
4049.7737556561))
((0 . "LWPOLYLINE") (100 . "AcDbEntity") (8 . "PLANTS") (62 . 94) (370 . 13) (100 . "AcDbPolyline") (90 . 2) (70 . 0)
(43 . 0.0) (10 6576.1686651584 3868.778280543) (10 6598.7930995475 3865.0071266968))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6576.1686651584 3868.778280543 0.0) (10 6569.7997609567 3888.9654580258 0.0) (10 6585.8565640707
3916.746771284 0.0) (10 6610.1053167421 3906.4860859728 0.0))
((0 . "LWPOLYLINE") (100 . "AcDbEntity") (8 . "PLANTS") (62 . 94) (370 . 13) (100 . "AcDbPolyline") (90 . 3) (70 . 0)
(43 . 0.0) (10 6591.2521493213 4023.3781674208) (10 6590.0541855204 4038.4615384615) (10 6583.7104072398
4049.7737556561))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6666.666402715 4102.5636877828 0.0) (10 6626.8708070261 4106.0800039173 0.0) (10 6618.0315475897
4057.2751847819 0.0) (10 6583.7104072398 4049.7737556561 0.0))
((0 . "LWPOLYLINE") (100 . "AcDbEntity") (8 . "PLANTS") (62 . 94) (370 . 13) (100 . "AcDbPolyline") (90 . 2) (70 . 0)
(43 . 0.0) (10 6583.7104072398 904.9773755656) (10 6583.7104072398 927.6018099548))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6640.2714932127 950.2262443439 0.0) (10 6623.2219491846 934.2069659919 0.0) (10 6596.2293167559
952.5241763554 0.0) (10 6583.7104072398 927.6018099548 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6583.7104072398 904.9773755656 0.0) (10 6610.3914884127 890.5073300629 0.0) (10 6658.3858936713
925.8827486424 0.0) (10 6666.1448847839 886.6848840857 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6587.4808823529 6881.5985294118 0.0) (10 6606.0650958551 6902.3647915054 0.0) (10 6638.894207102
6922.1709621229 0.0) (10 6666.666402715 6907.9942307693 0.0))
((0 . "LWPOLYLINE") (100 . "AcDbEntity") (8 . "PLANTS") (62 . 94) (370 . 13) (100 . "AcDbPolyline") (90 . 3) (70 . 0)
(43 . 0.0) (10 6610.1053167421 6779.7885746606) (10 6598.7930995475 6765.9101809955) (10 6587.4808823529
6764.7058823529))
((0 . "LWPOLYLINE") (100 . "AcDbEntity") (8 . "PLANTS") (62 . 94) (370 . 13) (100 . "AcDbPolyline") (90 . 2) (70 . 0)
(43 . 0.0) (10 6870.2863122172 6730.7692307692) (10 6822.2034997856 6730.6746752567))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.64103442) (40 .
1) (40 . 1) (40 . 1) (40 . 1) (10 6587.4808823529 452.4886877828 0.0) (10 6589.5143293928 431.6448496774 0.0) (10
6630.3447939444 398.7234268294 0.0) (10 6619.5579045351 368.2509500902 0.0) (10 6602.5643665158 361.9909502262 0.0))
((0 . "LWPOLYLINE") (100 . "AcDbEntity") (8 . "PLANTS") (62 . 94) (370 . 13) (100 . "AcDbPolyline") (90 . 2) (70 . 0)
(43 . 0.0) (10 6591.3572086269 4182.5880293449) (10 6591.2521493213 4128.9592760181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6591.2521493213 4128.9592760181 0.0) (10 6621.0590968983 4125.6074013651 0.0) (10 6658.5262507216
4140.2067612857 0.0) (10 6662.8959276018 4174.2081447964 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6591.2521493213 4023.3781674208 0.0) (10 6618.4941270232 4023.1774477028 0.0) (10 6631.312295649
4053.4813650359 0.0) (10 6659.1254524887 4053.5449095023 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6670.4376696833 3812.2171945701 0.0) (10 6650.6482119469 3801.1357654867 0.0) (10 6611.2628094543
3778.4114134161 0.0) (10 6591.2521493212 3800.9049773755 0.0))
((0 . "LWPOLYLINE") (100 . "AcDbEntity") (8 . "PLANTS") (62 . 94) (370 . 13) (100 . "AcDbPolyline") (90 . 3) (70 . 0)
(43 . 0.0) (10 6598.7930995475 3865.0071266968) (10 6598.645361991 3823.5294117647) (10 6591.2521493213
3800.9049773756))
((0 . "LWPOLYLINE") (100 . "AcDbEntity") (8 . "PLANTS") (62 . 94) (370 . 13) (100 . "AcDbPolyline") (90 . 2) (70 . 0)
(43 . 0.0) (10 6598.7930995475 3865.0071266968) (10 6613.8765837104 3865.0071266968))
((0 . "LWPOLYLINE") (100 . "AcDbEntity") (8 . "PLANTS") (62 . 94) (370 . 13) (100 . "AcDbPolyline") (90 . 2) (70 . 0)
(43 . 0.0) (10 6602.5643665158 343.1363122172) (10 6602.5643665158 361.9909502262))
((0 . "LWPOLYLINE") (100 . "AcDbEntity") (8 . "PLANTS") (62 . 94) (370 . 13) (100 . "AcDbPolyline") (90 . 3) (70 . 0)
(43 . 0.0) (10 6602.5643665158 343.1363122172) (10 6636.5010180995 325.3332579186) (10 6666.6664027149 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6606.334841629 1003.0175339367 0.0) (10 6597.5250377794 974.613569347 0.0) (10 6643.7906726846
978.7996409529 0.0) (10 6640.2714932127 950.2262443439 0.0))
((0 . "LWPOLYLINE") (100 . "AcDbEntity") (8 . "PLANTS") (62 . 94) (370 . 13) (100 . "AcDbPolyline") (90 . 2) (70 . 0)
(43 . 0.0) (10 6606.334841629 1003.0175339367) (10 6625.188800905 1014.3297511312))
((0 . "LWPOLYLINE") (100 . "AcDbEntity") (8 . "PLANTS") (62 . 94) (370 . 13) (100 . "AcDbPolyline") (90 . 2) (70 . 0)
(43 . 0.0) (10 6610.1053167421 6779.7885746606) (10 6628.9592760181 6787.3303167421))
((0 . "LWPOLYLINE") (100 . "AcDbEntity") (8 . "PLANTS") (62 . 94) (370 . 13) (100 . "AcDbPolyline") (90 . 3) (70 . 0)
(43 . 0.0) (10 6613.8765837104 3865.0071266968) (10 6613.7288461538 3898.9375565611) (10 6610.1053167421
3906.4860859729))
((0 . "LWPOLYLINE") (100 . "AcDbEntity") (8 . "PLANTS") (62 . 94) (370 . 13) (100 . "AcDbPolyline") (90 . 3) (70 . 0)
(43 . 0.0) (10 6647.8132352941 3914.0271493213) (10 6628.9592760181 3913.8790723982) (10 6610.1053167421
3906.4860859729))
((0 . "LWPOLYLINE") (100 . "AcDbEntity") (8 . "PLANTS") (62 . 94) (370 . 13) (100 . "AcDbPolyline") (90 . 2) (70 . 0)
(43 . 0.0) (10 6621.4175339367 516.5921945701) (10 6610.1053167421 524.1317873303))
((0 . "LWPOLYLINE") (100 . "AcDbEntity") (8 . "PLANTS") (62 . 94) (370 . 13) (100 . "AcDbPolyline") (90 . 3) (70 . 0)
(43 . 0.0) (10 6662.8959276018 3831.0704751131) (10 6621.4244343891 3863.803280543) (10 6613.8765837104
3865.0071266968))
((0 . "LWPOLYLINE") (100 . "AcDbEntity") (8 . "PLANTS") (62 . 94) (370 . 13) (100 . "AcDbPolyline") (90 . 3) (70 . 0)
(43 . 0.0) (10 6621.4175339367 516.5921945701) (10 6646.7636877828 437.4066742081) (10 6659.1254524887 373.3031674208))
((0 . "LWPOLYLINE") (100 . "AcDbEntity") (8 . "PLANTS") (62 . 94) (370 . 13) (100 . "AcDbPolyline") (90 . 2) (70 . 0)
(43 . 0.0) (10 6621.4175339367 516.5921945701) (10 6628.8367829514 524.0114435849))
((0 . "LWPOLYLINE") (100 . "AcDbEntity") (8 . "PLANTS") (62 . 94) (370 . 13) (100 . "AcDbPolyline") (90 . 2) (70 . 0)
(43 . 0.0) (10 6625.188800905 1021.8693438914) (10 6625.188800905 1014.3297511312))
((0 . "LWPOLYLINE") (100 . "AcDbEntity") (8 . "PLANTS") (62 . 94) (370 . 13) (100 . "AcDbPolyline") (90 . 2) (70 . 0)
(43 . 0.0) (10 6625.188800905 1014.3297511312) (10 6632.7297511312 1010.5571266968))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6734.5397058824 6776.0180995475 0.0) (10 6705.6142849064 6805.5268411931 0.0) (10 6663.5039368984
6773.1004948443 0.0) (10 6628.9592760181 6787.3303167421 0.0))
((0 . "LWPOLYLINE") (100 . "AcDbEntity") (8 . "PLANTS") (62 . 94) (370 . 13) (100 . "AcDbPolyline") (90 . 2) (70 . 0)
(43 . 0.0) (10 6628.9592760181 6787.3303167421) (10 6636.5010180995 6832.5791855204))
((0 . "LWPOLYLINE") (100 . "AcDbEntity") (8 . "PLANTS") (62 . 94) (370 . 13) (100 . "AcDbPolyline") (90 . 3) (70 . 0)
(43 . 0.0) (10 6847.0172464348 6478.4015843227) (10 6847.6618778281 6478.2777149321) (10 6924.9625565611
6478.129638009))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5557346633) (40
. 1) (40 . 1) (40 . 1) (40 . 1) (10 6666.666402715 6907.9942307692 0.0) (10 6669.4097371163 6890.5151036548 0.0) (10
6641.0588414037 6873.5882470775 0.0) (10 6629.8505680718 6848.2635464893 0.0) (10 6636.5010180996 6832.5791855203 0.0))
((0 . "LWPOLYLINE") (100 . "AcDbEntity") (8 . "PLANTS") (62 . 94) (370 . 13) (100 . "AcDbPolyline") (90 . 2) (70 . 0)
(43 . 0.0) (10 6674.2081447964 6836.3496606335) (10 6636.5010180995 6832.5791855204))
((0 . "LWPOLYLINE") (100 . "AcDbEntity") (8 . "PLANTS") (62 . 94) (370 . 13) (100 . "AcDbPolyline") (90 . 3) (70 . 0)
(43 . 0.0) (10 6700.8793698724 932.9975308706) (10 6674.2081447964 945.4055429864) (10 6640.2714932127 950.2262443439))
((0 . "LWPOLYLINE") (100 . "AcDbEntity") (8 . "PLANTS") (62 . 94) (370 . 13) (100 . "AcDbPolyline") (90 . 3) (70 . 0)
(43 . 0.0) (10 6647.8132352941 3914.0271493213) (10 6655.5088235294 3900.1485294118) (10 6674.2081447964
3898.9437782805))
((0 . "LWPOLYLINE") (100 . "AcDbEntity") (8 . "PLANTS") (62 . 94) (370 . 13) (100 . "AcDbPolyline") (90 . 3) (70 . 0)
(43 . 0.0) (10 6666.6664027149 3929.110520362) (10 6655.3610859729 3925.1847285068) (10 6647.8132352941
3914.0271493213))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.359360043) (40 .
1) (40 . 1) (40 . 1) (40 . 1) (10 6651.5837104072 7051.2817873302 0.0) (10 6665.8141975944 7045.5041155367 0.0) (10
6710.3776204161 7052.7712604863 0.0) (10 6744.7672882411 7016.9470356598 0.0) (10 6772.2476244344 7013.5746606334 0.0))
((0 . "LWPOLYLINE") (100 . "AcDbEntity") (8 . "PLANTS") (62 . 94) (370 . 13) (100 . "AcDbPolyline") (90 . 2) (70 . 0)
(43 . 0.0) (10 6651.5837104072 252.6385746606) (10 6670.4376696833 256.411199095))
((0 . "LWPOLYLINE") (100 . "AcDbEntity") (8 . "PLANTS") (62 . 94) (370 . 13) (100 . "AcDbPolyline") (90 . 2) (70 . 0)
(43 . 0.0) (10 6674.2081447964 4023.3781674208) (10 6659.1254524887 4053.5449095023))
((0 . "LWPOLYLINE") (100 . "AcDbEntity") (8 . "PLANTS") (62 . 94) (370 . 13) (100 . "AcDbPolyline") (90 . 2) (70 . 0)
(43 . 0.0) (10 6666.6664027149 4068.6270361991) (10 6659.1254524887 4053.5449095023))
((0 . "LWPOLYLINE") (100 . "AcDbEntity") (8 . "PLANTS") (62 . 94) (370 . 13) (100 . "AcDbPolyline") (90 . 2) (70 . 0)
(43 . 0.0) (10 6659.1254524887 3996.9838235294) (10 6666.6664027149 3970.5882352941))
((0 . "LWPOLYLINE") (100 . "AcDbEntity") (8 . "PLANTS") (62 . 94) (370 . 13) (100 . "AcDbPolyline") (90 . 2) (70 . 0)
(43 . 0.0) (10 6674.2081447964 4023.3781674208) (10 6659.1254524887 3996.9838235294))
((0 . "LWPOLYLINE") (100 . "AcDbEntity") (8 . "PLANTS") (62 . 94) (370 . 13) (100 . "AcDbPolyline") (90 . 3) (70 . 0)
(43 . 0.0) (10 6670.4376696833 980.3930995475) (10 6662.8959276018 984.1628959276) (10 6659.1254524887 980.3930995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6672.3225113122 329.9406108597 0.0) (10 6654.5500675421 335.3905030192 0.0) (10 6661.3570288668
361.7465616518 0.0) (10 6659.1254524887 373.3031674208 0.0))
((0 . "LWPOLYLINE") (100 . "AcDbEntity") (8 . "PLANTS") (62 . 94) (370 . 13) (100 . "AcDbPolyline") (90 . 3) (70 . 0)
(43 . 0.0) (10 6689.2908371041 392.1578054299) (10 6666.6733031674 374.5080316742) (10 6659.1254524887 373.3031674208))
((0 . "LWPOLYLINE") (100 . "AcDbEntity") (8 . "PLANTS") (62 . 94) (370 . 13) (100 . "AcDbPolyline") (90 . 2) (70 . 0)
(43 . 0.0) (10 6662.8959276018 4174.2081447964) (10 6662.8959276018 4239.8190045249))
((0 . "LWPOLYLINE") (100 . "AcDbEntity") (8 . "PLANTS") (62 . 94) (370 . 13) (100 . "AcDbPolyline") (90 . 2) (70 . 0)
(43 . 0.0) (10 6715.6865384615 4136.5003393665) (10 6739.9311615382 4164.7658214941))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6731.836463158 4193.0972658249 0.0) (10 6707.4313482235 4192.6590432222 0.0) (10 6688.9206595898
4156.3032233729 0.0) (10 6662.8959276018 4174.2081447964 0.0))
((0 . "LWPOLYLINE") (100 . "AcDbEntity") (8 . "PLANTS") (62 . 94) (370 . 13) (100 . "AcDbPolyline") (90 . 3) (70 . 0)
(43 . 0.0) (10 6662.8959276018 3831.0704751131) (10 6662.8959276018 3823.5294117647) (10 6670.4376696833
3819.7582579186))
((0 . "LWPOLYLINE") (100 . "AcDbEntity") (8 . "PLANTS") (62 . 94) (370 . 13) (100 . "AcDbPolyline") (90 . 3) (70 . 0)
(43 . 0.0) (10 6662.8959276018 3831.0704751131) (10 6674.0597285068 3849.925) (10 6674.2081447964 3898.9437782805))
((0 . "LWPOLYLINE") (100 . "AcDbEntity") (8 . "PLANTS") (62 . 94) (370 . 13) (100 . "AcDbPolyline") (90 . 2) (70 . 0)
(43 . 0.0) (10 6711.9152714932 6907.9942307692) (10 6666.6664027149 6907.9942307692))
((0 . "LWPOLYLINE") (100 . "AcDbEntity") (8 . "PLANTS") (62 . 94) (370 . 13) (100 . "AcDbPolyline") (90 . 2) (70 . 0)
(43 . 0.0) (10 6670.4376696833 4113.8759049774) (10 6666.6664027149 4121.4182126697))
((0 . "LWPOLYLINE") (100 . "AcDbEntity") (8 . "PLANTS") (62 . 94) (370 . 13) (100 . "AcDbPolyline") (90 . 2) (70 . 0)
(43 . 0.0) (10 6666.6664027149 4068.6270361991) (10 6666.6664027149 4102.5636877828))
((0 . "LWPOLYLINE") (100 . "AcDbEntity") (8 . "PLANTS") (62 . 94) (370 . 13) (100 . "AcDbPolyline") (90 . 2) (70 . 0)
(43 . 0.0) (10 6666.6664027149 4102.5636877828) (10 6670.4376696833 4113.8759049774))
((0 . "LWPOLYLINE") (100 . "AcDbEntity") (8 . "PLANTS") (62 . 94) (370 . 13) (100 . "AcDbPolyline") (90 . 2) (70 . 0)
(43 . 0.0) (10 6696.8325791855 4072.3981900452) (10 6666.6664027149 4068.6270361991))
((0 . "LWPOLYLINE") (100 . "AcDbEntity") (8 . "PLANTS") (62 . 94) (370 . 13) (100 . "AcDbPolyline") (90 . 2) (70 . 0)
(43 . 0.0) (10 6666.6664027149 3970.5882352941) (10 6704.374321267 3966.817081448))
((0 . "LWPOLYLINE") (100 . "AcDbEntity") (8 . "PLANTS") (62 . 94) (370 . 13) (100 . "AcDbPolyline") (90 . 2) (70 . 0)
(43 . 0.0) (10 6666.6664027149 3929.110520362) (10 6666.6664027149 3970.5882352941))
((0 . "LWPOLYLINE") (100 . "AcDbEntity") (8 . "PLANTS") (62 . 94) (370 . 13) (100 . "AcDbPolyline") (90 . 2) (70 . 0)
(43 . 0.0) (10 6666.6664027149 3929.110520362) (10 6689.2908371041 3929.110520362))
((0 . "LWPOLYLINE") (100 . "AcDbEntity") (8 . "PLANTS") (62 . 94) (370 . 13) (100 . "AcDbPolyline") (90 . 3) (70 . 0)
(43 . 0.0) (10 6666.6664027149 316.742081448) (10 6666.8141402715 275.2705882353) (10 6670.4376696833 267.7234162896))
((0 . "LWPOLYLINE") (100 . "AcDbEntity") (8 . "PLANTS") (62 . 94) (370 . 13) (100 . "AcDbPolyline") (90 . 2) (70 . 0)
(43 . 0.0) (10 6672.3225113122 329.9406108597) (10 6666.6664027149 316.742081448))
((0 . "LWPOLYLINE") (100 . "AcDbEntity") (8 . "PLANTS") (62 . 94) (370 . 13) (100 . "AcDbPolyline") (90 . 2) (70 . 0)
(43 . 0.0) (10 6670.4376696833 4113.8759049774) (10 6693.0621040724 4128.9592760181))
((0 . "LWPOLYLINE") (100 . "AcDbEntity") (8 . "PLANTS") (62 . 94) (370 . 13) (100 . "AcDbPolyline") (90 . 2) (70 . 0)
(43 . 0.0) (10 6670.4376696833 3812.2171945701) (10 6670.4376696833 3819.7582579186))
((0 . "LWPOLYLINE") (100 . "AcDbEntity") (8 . "PLANTS") (62 . 94) (370 . 13) (100 . "AcDbPolyline") (90 . 3) (70 . 0)
(43 . 0.0) (10 6670.4376696833 3819.7582579186) (10 6693.0621040724 3833.7849547511) (10 6726.9987556561
3838.6127828054))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6749.6231900453 3804.6761312217 0.0) (10 6729.9317045484 3781.6658449723 0.0) (10 6684.1244553055
3782.7742690685 0.0) (10 6670.4376696833 3812.2171945701 0.0))
((0 . "LWPOLYLINE") (100 . "AcDbEntity") (8 . "PLANTS") (62 . 94) (370 . 13) (100 . "AcDbPolyline") (90 . 2) (70 . 0)
(43 . 0.0) (10 6670.4376696833 256.411199095) (10 6670.4376696833 267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6726.9987556561 305.4298642534 0.0) (10 6716.2827662378 279.0623950767 0.0) (10 6684.4050403518
289.8515705936 0.0) (10 6670.4376696833 267.7234162896 0.0))
((0 . "LWPOLYLINE") (100 . "AcDbEntity") (8 . "PLANTS") (62 . 94) (370 . 13) (100 . "AcDbPolyline") (90 . 3) (70 . 0)
(43 . 0.0) (10 6670.4376696833 256.411199095) (10 6689.2908371041 241.4816742081) (10 6726.9987556561 241.3263574661))
((0 . "LWPOLYLINE") (100 . "AcDbEntity") (8 . "PLANTS") (62 . 94) (370 . 13) (100 . "AcDbPolyline") (90 . 3) (70 . 0)
(43 . 0.0) (10 6672.3225113122 329.9406108597) (10 6674.2081447964 335.596719457) (10 6680.8066742081 337.4802036199))
((0 . "LWPOLYLINE") (100 . "AcDbEntity") (8 . "PLANTS") (62 . 94) (370 . 13) (100 . "AcDbPolyline") (90 . 2) (70 . 0)
(43 . 0.0) (10 6672.3225113122 329.9406108597) (10 6680.8066742081 337.4802036199))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6674.2081447964 6836.3496606335 0.0) (10 6700.0730461439 6821.1948618268 0.0) (10 6734.3991917226
6832.155854986 0.0) (10 6760.9354072398 6840.1209276018 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6674.2081447964 6836.3496606335 0.0) (10 6666.0523685017 6861.6422800014 0.0) (10 6691.1871717923
6879.3116867408 0.0) (10 6711.9152714932 6874.0575791855 0.0))
((0 . "LWPOLYLINE") (100 . "AcDbEntity") (8 . "PLANTS") (62 . 94) (370 . 13) (100 . "AcDbPolyline") (90 . 2) (70 . 0)
(43 . 0.0) (10 6674.2081447964 4023.3781674208) (10 6689.2908371041 4034.6903846154))
((0 . "LWPOLYLINE") (100 . "AcDbEntity") (8 . "PLANTS") (62 . 94) (370 . 13) (100 . "AcDbPolyline") (90 . 2) (70 . 0)
(43 . 0.0) (10 6674.2081447964 3898.9437782805) (10 6689.2908371041 3906.4860859729))
((0 . "LWPOLYLINE") (100 . "AcDbEntity") (8 . "PLANTS") (62 . 94) (370 . 13) (100 . "AcDbPolyline") (90 . 3) (70 . 0)
(43 . 0.0) (10 6708.1447963801 7006.032918552) (10 6693.0621040724 7007.2372171946) (10 6677.9786199095
7017.3451357466))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6680.8066742081 337.4802036199 0.0) (10 6693.4038676396 310.2502085886 0.0) (10 6735.9859533962
356.3755995902 0.0) (10 6711.9152714932 373.3031674208 0.0))
((0 . "LWPOLYLINE") (100 . "AcDbEntity") (8 . "PLANTS") (62 . 94) (370 . 13) (100 . "AcDbPolyline") (90 . 3) (70 . 0)
(43 . 0.0) (10 6680.8066742081 337.4802036199) (10 6688.0929864253 361.9909502262) (10 6685.520361991 373.3031674208))
((0 . "LWPOLYLINE") (100 . "AcDbEntity") (8 . "PLANTS") (62 . 94) (370 . 13) (100 . "AcDbPolyline") (90 . 2) (70 . 0)
(43 . 0.0) (10 6680.8066742081 337.4802036199) (10 6685.520361991 339.3665158371))
((0 . "LWPOLYLINE") (100 . "AcDbEntity") (8 . "PLANTS") (62 . 94) (370 . 13) (100 . "AcDbPolyline") (90 . 2) (70 . 0)
(43 . 0.0) (10 6689.2908371041 3929.110520362) (10 6689.2908371041 3906.4860859729))
((0 . "LWPOLYLINE") (100 . "AcDbEntity") (8 . "PLANTS") (62 . 94) (370 . 13) (100 . "AcDbPolyline") (90 . 3) (70 . 0)
(43 . 0.0) (10 6689.2908371041 3929.110520362) (10 6699.546719457 3936.6578054299) (10 6708.1447963801 3955.5048642534))
((0 . "LWPOLYLINE") (100 . "AcDbEntity") (8 . "PLANTS") (62 . 94) (370 . 13) (100 . "AcDbPolyline") (90 . 3) (70 . 0)
(43 . 0.0) (10 6719.4570135747 3898.9437782805) (10 6704.374321267 3905.4294117647) (10 6689.2908371041
3906.4860859729))
((0 . "LWPOLYLINE") (100 . "AcDbEntity") (8 . "PLANTS") (62 . 94) (370 . 13) (100 . "AcDbPolyline") (90 . 2) (70 . 0)
(43 . 0.0) (10 6689.2908371041 392.1578054299) (10 6708.1447963801 392.1578054299))
((0 . "LWPOLYLINE") (100 . "AcDbEntity") (8 . "PLANTS") (62 . 94) (370 . 13) (100 . "AcDbPolyline") (90 . 3) (70 . 0)
(43 . 0.0) (10 6689.2908371041 392.1578054299) (10 6690.4950226244 411.0096153846) (10 6700.6030542986 422.3218325792))
((0 . "LWPOLYLINE") (100 . "AcDbEntity") (8 . "PLANTS") (62 . 94) (370 . 13) (100 . "AcDbPolyline") (90 . 3) (70 . 0)
(43 . 0.0) (10 6719.4570135747 6923.0769230769) (10 6711.9090497738 6934.2411764706) (10 6693.0621040724
6945.7013574661))
((0 . "LWPOLYLINE") (100 . "AcDbEntity") (8 . "PLANTS") (62 . 94) (370 . 13) (100 . "AcDbPolyline") (90 . 2) (70 . 0)
(43 . 0.0) (10 6719.4570135747 411.0096153846) (10 6700.6030542986 422.3218325792))
((0 . "LWPOLYLINE") (100 . "AcDbEntity") (8 . "PLANTS") (62 . 94) (370 . 13) (100 . "AcDbPolyline") (90 . 3) (70 . 0)
(43 . 0.0) (10 6708.1447963801 437.4066742081) (10 6700.6030542986 429.8642533937) (10 6700.6030542986 422.3218325792))
((0 . "LWPOLYLINE") (100 . "AcDbEntity") (8 . "PLANTS") (62 . 94) (370 . 13) (100 . "AcDbPolyline") (90 . 2) (70 . 0)
(43 . 0.0) (10 6708.1447963801 3955.5048642534) (10 6704.374321267 3966.817081448))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2042261607)
(40 . 0.4906728956) (40 . 1) (40 . 1) (40 . 1) (40 . 1) (10 6776.0180995475 3993.2126696832 0.0) (10 6784.5992612831
4003.0103794573 0.0) (10 6788.2213869953 4024.7009684456 0.0) (10 6730.8845307739 4014.9193646427 0.0) (10
6706.1431996551 3993.1588031723 0.0) (10 6704.374321267 3966.817081448 0.0))
((0 . "LWPOLYLINE") (100 . "AcDbEntity") (8 . "PLANTS") (62 . 94) (370 . 13) (100 . "AcDbPolyline") (90 . 2) (70 . 0)
(43 . 0.0) (10 6715.6865384615 4136.5003393665) (10 6708.1447963801 4132.7304298643))
((0 . "LWPOLYLINE") (100 . "AcDbEntity") (8 . "PLANTS") (62 . 94) (370 . 13) (100 . "AcDbPolyline") (90 . 3) (70 . 0)
(43 . 0.0) (10 6768.4763574661 3981.9004524887) (10 6730.7692307692 3960.3320135747) (10 6708.1447963801
3955.5048642534))
((0 . "LWPOLYLINE") (100 . "AcDbEntity") (8 . "PLANTS") (62 . 94) (370 . 13) (100 . "AcDbPolyline") (90 . 2) (70 . 0)
(43 . 0.0) (10 6711.9152714932 373.3031674208) (10 6708.1447963801 392.1578054299))
((0 . "LWPOLYLINE") (100 . "AcDbEntity") (8 . "PLANTS") (62 . 94) (370 . 13) (100 . "AcDbPolyline") (90 . 2) (70 . 0)
(43 . 0.0) (10 6719.4570135747 411.0096153846) (10 6708.1447963801 392.1578054299))
((0 . "LWPOLYLINE") (100 . "AcDbEntity") (8 . "PLANTS") (62 . 94) (370 . 13) (100 . "AcDbPolyline") (90 . 2) (70 . 0)
(43 . 0.0) (10 6711.9152714932 6907.9942307692) (10 6711.9152714932 6874.0575791855))
((0 . "LWPOLYLINE") (100 . "AcDbEntity") (8 . "PLANTS") (62 . 94) (370 . 13) (100 . "AcDbPolyline") (90 . 3) (70 . 0)
(43 . 0.0) (10 6719.4570135747 6923.0769230769) (10 6719.4570135747 6915.5351809955) (10 6711.9152714932
6907.9942307692))
((0 . "LWPOLYLINE") (100 . "AcDbEntity") (8 . "PLANTS") (62 . 94) (370 . 13) (100 . "AcDbPolyline") (90 . 2) (70 . 0)
(43 . 0.0) (10 6719.4570135747 6866.5158371041) (10 6711.9152714932 6874.0575791855))
((0 . "LWPOLYLINE") (100 . "AcDbEntity") (8 . "PLANTS") (62 . 94) (370 . 13) (100 . "AcDbPolyline") (90 . 3) (70 . 0)
(43 . 0.0) (10 6711.9152714932 4102.5636877828) (10 6719.3085972851 4121.4182126697) (10 6715.6865384615
4136.5003393665))
((0 . "LWPOLYLINE") (100 . "AcDbEntity") (8 . "PLANTS") (62 . 94) (370 . 13) (100 . "AcDbPolyline") (90 . 2) (70 . 0)
(43 . 0.0) (10 6711.9152714932 373.3031674208) (10 6749.6231900452 373.3031674208))
((0 . "LWPOLYLINE") (100 . "AcDbEntity") (8 . "PLANTS") (62 . 94) (370 . 13) (100 . "AcDbPolyline") (90 . 2) (70 . 0)
(43 . 0.0) (10 6719.4570135747 6923.0769230769) (10 6742.0814479638 6926.84739819))
((0 . "LWPOLYLINE") (100 . "AcDbEntity") (8 . "PLANTS") (62 . 94) (370 . 13) (100 . "AcDbPolyline") (90 . 3) (70 . 0)
(43 . 0.0) (10 6723.2274886878 3883.8616515837) (10 6719.4570135747 3887.631561086) (10 6719.4570135747
3898.9437782805))
((0 . "LWPOLYLINE") (100 . "AcDbEntity") (8 . "PLANTS") (62 . 94) (370 . 13) (100 . "AcDbPolyline") (90 . 2) (70 . 0)
(43 . 0.0) (10 6719.4570135747 3898.9437782805) (10 6734.5397058824 3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6719.4570135747 411.0096153846 0.0) (10 6739.2933723195 431.8253799243 0.0) (10 6769.5953714562
409.7233821208 0.0) (10 6760.9354072398 384.6153846154 0.0))
((0 . "LWPOLYLINE") (100 . "AcDbEntity") (8 . "PLANTS") (62 . 94) (370 . 13) (100 . "AcDbPolyline") (90 . 2) (70 . 0)
(43 . 0.0) (10 6734.5397058824 6776.0180995475) (10 6723.2274886878 6753.3936651584))
((0 . "LWPOLYLINE") (100 . "AcDbEntity") (8 . "PLANTS") (62 . 94) (370 . 13) (100 . "AcDbPolyline") (90 . 3) (70 . 0)
(43 . 0.0) (10 6723.2274886878 3883.8616515837) (10 6723.3752262443 3849.925) (10 6726.9987556561 3838.6127828054))
((0 . "LWPOLYLINE") (100 . "AcDbEntity") (8 . "PLANTS") (62 . 94) (370 . 13) (100 . "AcDbPolyline") (90 . 2) (70 . 0)
(43 . 0.0) (10 6723.2274886878 3883.8616515837) (10 6742.0814479638 3887.631561086))
((0 . "LWPOLYLINE") (100 . "AcDbEntity") (8 . "PLANTS") (62 . 94) (370 . 13) (100 . "AcDbPolyline") (90 . 3) (70 . 0)
(43 . 0.0) (10 6749.6231900452 3804.6761312217) (10 6741.0251131222 3834.6869909502) (10 6726.9987556561
3838.6127828054))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6726.9987556561 241.3263574661 0.0) (10 6744.2996813194 218.3403273418 0.0) (10 6782.5970226827
224.8855670985 0.0) (10 6806.1842760181 237.556561086 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6783.559841629 297.8874434389 0.0) (10 6772.4252561015 269.0879575961 0.0) (10 6729.1001849947
276.1590340112 0.0) (10 6726.9987556561 241.3263574661 0.0))
((0 . "LWPOLYLINE") (100 . "AcDbEntity") (8 . "PLANTS") (62 . 94) (370 . 13) (100 . "AcDbPolyline") (90 . 2) (70 . 0)
(43 . 0.0) (10 6734.5397058824 6776.0180995475) (10 6764.7058823529 6783.559841629))
((0 . "LWPOLYLINE") (100 . "AcDbEntity") (8 . "PLANTS") (62 . 94) (370 . 13) (100 . "AcDbPolyline") (90 . 2) (70 . 0)
(43 . 0.0) (10 6749.6231900452 3898.9437782805) (10 6734.5397058824 3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6821.2669683258 3906.4860859729 0.0) (10 6814.2359747616 3938.9531099868 0.0) (10 6729.8066383488
3957.0884467805 0.0) (10 6734.5397058823 3910.2559954751 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6802.4130090498 373.3031674208 0.0) (10 6815.4048487722 410.0004190276 0.0) (10 6777.7870848321
431.8816966148 0.0) (10 6777.2375113209 464.2501619465 0.0))
((0 . "LWPOLYLINE") (100 . "AcDbEntity") (8 . "PLANTS") (62 . 94) (370 . 13) (100 . "AcDbPolyline") (90 . 3) (70 . 0)
(43 . 0.0) (10 6768.4763574661 3880.0904977376) (10 6749.6294117647 3880.2451357466) (10 6742.0814479638
3887.631561086))
((0 . "LWPOLYLINE") (100 . "AcDbEntity") (8 . "PLANTS") (62 . 94) (370 . 13) (100 . "AcDbPolyline") (90 . 2) (70 . 0)
(43 . 0.0) (10 6749.6231900452 3898.9437782805) (10 6742.0814479638 3887.631561086))
((0 . "LWPOLYLINE") (100 . "AcDbEntity") (8 . "PLANTS") (62 . 94) (370 . 13) (100 . "AcDbPolyline") (90 . 2) (70 . 0)
(43 . 0.0) (10 6768.4763574661 3895.1738687783) (10 6749.6231900452 3898.9437782805))
((0 . "LWPOLYLINE") (100 . "AcDbEntity") (8 . "PLANTS") (62 . 94) (370 . 13) (100 . "AcDbPolyline") (90 . 3) (70 . 0)
(43 . 0.0) (10 6749.6231900452 3804.6761312217) (10 6772.2476244344 3797.282239819) (10 6825.0374434389
3795.2488687783))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6783.559841629 297.8874434389 0.0) (10 6764.5953157195 318.2544423351 0.0) (10 6748.4704607679
344.2050798745 0.0) (10 6749.6231900452 373.3031674208 0.0))
((0 . "LWPOLYLINE") (100 . "AcDbEntity") (8 . "PLANTS") (62 . 94) (370 . 13) (100 . "AcDbPolyline") (90 . 3) (70 . 0)
(43 . 0.0) (10 6749.6231900452 373.3031674208) (10 6753.3936651584 380.8455882353) (10 6760.9354072398 384.6153846154))
((0 . "LWPOLYLINE") (100 . "AcDbEntity") (8 . "PLANTS") (62 . 94) (370 . 13) (100 . "AcDbPolyline") (90 . 2) (70 . 0)
(43 . 0.0) (10 6757.1641402715 6979.6380090498) (10 6783.559841629 6964.5553167421))
((0 . "LWPOLYLINE") (100 . "AcDbEntity") (8 . "PLANTS") (62 . 94) (370 . 13) (100 . "AcDbPolyline") (90 . 2) (70 . 0)
(43 . 0.0) (10 6760.9354072398 6840.1209276018) (10 6764.7058823529 6828.8087104072))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6809.9547511312 6919.3064479638 0.0) (10 6825.6699722163 6874.8569118629 0.0) (10 6768.8104956266
6874.3267365473 0.0) (10 6760.9354072398 6840.1209276018 0.0))
((0 . "LWPOLYLINE") (100 . "AcDbEntity") (8 . "PLANTS") (62 . 94) (370 . 13) (100 . "AcDbPolyline") (90 . 2) (70 . 0)
(43 . 0.0) (10 6802.4130090498 373.3031674208) (10 6760.9354072398 384.6153846154))
((0 . "LWPOLYLINE") (100 . "AcDbEntity") (8 . "PLANTS") (62 . 94) (370 . 13) (100 . "AcDbPolyline") (90 . 2) (70 . 0)
(43 . 0.0) (10 6764.7058823529 6783.559841629) (10 6764.7058823529 6828.8087104072))
((0 . "LWPOLYLINE") (100 . "AcDbEntity") (8 . "PLANTS") (62 . 94) (370 . 13) (100 . "AcDbPolyline") (90 . 3) (70 . 0)
(43 . 0.0) (10 6855.2036199095 6840.1209276018) (10 6825.0374434389 6839.9726244344) (10 6764.7058823529
6828.8087104072))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6764.7058823529 6783.559841629 0.0) (10 6793.8728489386 6766.0321552339 0.0) (10 6831.4142922411
6788.6374380161 0.0) (10 6862.745361991 6776.0180995475 0.0))
((0 . "LWPOLYLINE") (100 . "AcDbEntity") (8 . "PLANTS") (62 . 94) (370 . 13) (100 . "AcDbPolyline") (90 . 2) (70 . 0)
(43 . 0.0) (10 6768.4763574661 3880.0904977376) (10 6768.4763574661 3895.1738687783))
((0 . "LWPOLYLINE") (100 . "AcDbEntity") (8 . "PLANTS") (62 . 94) (370 . 13) (100 . "AcDbPolyline") (90 . 3) (70 . 0)
(43 . 0.0) (10 6768.4763574661 3895.1738687783) (10 6806.1842760181 3899.0921945701) (10 6821.2669683258
3906.4860859729))
((0 . "LWPOLYLINE") (100 . "AcDbEntity") (8 . "PLANTS") (62 . 94) (370 . 13) (100 . "AcDbPolyline") (90 . 3) (70 . 0)
(43 . 0.0) (10 6768.4763574661 3880.0904977376) (10 6776.025 3869.8349547511) (10 6794.8720588235 3865.0071266968))
((0 . "LWPOLYLINE") (100 . "AcDbEntity") (8 . "PLANTS") (62 . 94) (370 . 13) (100 . "AcDbPolyline") (90 . 3) (70 . 0)
(43 . 0.0) (10 6798.6425339367 6983.4084841629) (10 6783.7075791855 6994.721040724) (10 6772.2476244344
7013.5746606335))
((0 . "SPLINE") (100 . "AcDbEntity") (8 . "PLANTS") (62 . 94) (370 . 13) (100 . "AcDbSpline") (70 . 0) (71 . 3) (72 .
13) (73 . 9) (74 . 0) (42 . 0.0000001) (43 . 0.0000001) (40 . 0.0) (40 . 0.0) (40 . 0.0) (40 . 0.0) (40 . 0.1534283113)
(40 . 0.3862672661) (40 . 0.6717170702) (40 . 0.7493505795) (40 . 0.881634943) (40 . 1) (40 . 1) (40 . 1) (40 . 1) (10
6885.3697963802 6998.4919683258 0.0) (10 6884.9459012673 7013.1555060814 0.0) (10 6854.8287043027 7024.8864736908 0.0)
(10 6835.6989776511 7077.0418355373 0.0) (10 6769.2887008757 7108.8091770332 0.0) (10 6766.7244382961 7067.8451231073
0.0) (10 6782.1171390312 7038.6310256594 0.0) (10 6781.3760707123 7020.9882381066 0.0) (10 6772.2476244344
7013.5746606335 0.0))
((0 . "LWPOLYLINE") (100 . "AcDbEntity") (8 . "PLANTS") (62 . 94) (370 . 13) (100 . "AcDbPolyline") (90 . 2) (70 . 0)
(43 . 0.0) (10 6783.559841629 6923.0769230769) (10 6809.9547511312 6919.3064479638))
((0 . "LWPOLYLINE") (100 . "AcDbEntity") (8 . "PLANTS") (62 . 94) (370 . 13) (100 . "AcDbPolyline") (90 . 2) (70 . 0)
(43 . 0.0) (10 6783.559841629 297.8874434389) (10 6798.6425339367 297.8874434389))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6805.0759279899 3733.0316742081 0.0) (10 6838.5835002472 3735.4543248909 0.0) (10 6823.2216936793
3778.9265985715 0.0) (10 6825.0374434389 3795.2488687783 0.0))
((0 . "LWPOLYLINE") (100 . "AcDbEntity") (8 . "PLANTS") (62 . 94) (370 . 13) (100 . "AcDbPolyline") (90 . 3) (70 . 0)
(43 . 0.0) (10 6859.2957148391 3839.897791483) (10 6836.3496606335 3852.6457013575) (10 6794.8720588235
3865.0071266968))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6794.8720588235 3865.0071266968 0.0) (10 6784.6834366138 3833.4897215024 0.0) (10 6833.2665013801
3828.3302374817 0.0) (10 6825.0374434389 3795.2488687783 0.0))
((0 . "LWPOLYLINE") (100 . "AcDbEntity") (8 . "PLANTS") (62 . 94) (370 . 13) (100 . "AcDbPolyline") (90 . 3) (70 . 0)
(43 . 0.0) (10 6798.6425339367 6983.4084841629) (10 6799.846719457 6964.5553167421) (10 6828.8087104072 6926.84739819))
((0 . "LWPOLYLINE") (100 . "AcDbEntity") (8 . "PLANTS") (62 . 94) (370 . 13) (100 . "AcDbPolyline") (90 . 3) (70 . 0)
(43 . 0.0) (10 6798.6425339367 6983.4084841629) (10 6806.1842760181 6984.6127828054) (10 6821.2669683258
6998.4919683258))
((0 . "LWPOLYLINE") (100 . "AcDbEntity") (8 . "PLANTS") (62 . 94) (370 . 13) (100 . "AcDbPolyline") (90 . 3) (70 . 0)
(43 . 0.0) (10 6798.6425339367 297.8874434389) (10 6806.029638009 286.5752262443) (10 6806.1842760181 237.556561086))
((0 . "LWPOLYLINE") (100 . "AcDbEntity") (8 . "PLANTS") (62 . 94) (370 . 13) (100 . "AcDbPolyline") (90 . 2) (70 . 0)
(43 . 0.0) (10 6798.6425339367 297.8874434389) (10 6809.9547511312 316.742081448))
((0 . "LWPOLYLINE") (100 . "AcDbEntity") (8 . "PLANTS") (62 . 94) (370 . 13) (100 . "AcDbPolyline") (90 . 2) (70 . 0)
(43 . 0.0) (10 6802.4130090498 373.3031674208) (10 6809.9547511312 369.5333710407))
((0 . "LWPOLYLINE") (100 . "AcDbEntity") (8 . "PLANTS") (62 . 94) (370 . 13) (100 . "AcDbPolyline") (90 . 2) (70 . 0)
(43 . 0.0) (10 6821.2669683258 6998.4919683258) (10 6806.1842760181 7043.7408371041))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.301489717)
(40 . 0.6086688796) (40 . 1) (40 . 1) (40 . 1) (40 . 1) (10 6907.9942307693 256.4111990949 0.0) (10 6899.2104740012
251.0468549844 0.0) (10 6878.1404152809 247.5541918759 0.0) (10 6844.7886701773 231.9620360665 0.0) (10 6819.4638020933
228.7224307934 0.0) (10 6806.1842760181 237.556561086 0.0))
((0 . "LWPOLYLINE") (100 . "AcDbEntity") (8 . "PLANTS") (62 . 94) (370 . 13) (100 . "AcDbPolyline") (90 . 3) (70 . 0)
(43 . 0.0) (10 6828.8087104072 6926.84739819) (10 6821.2607466063 6920.503959276) (10 6809.9547511312 6919.3064479638))
((0 . "LWPOLYLINE") (100 . "AcDbEntity") (8 . "PLANTS") (62 . 94) (370 . 13) (100 . "AcDbPolyline") (90 . 2) (70 . 0)
(43 . 0.0) (10 6809.9547511312 369.5333710407) (10 6809.9547511312 316.742081448))
((0 . "SPLINE") (100 . "AcDbEntity") (8 . "PLANTS") (62 . 94) (370 . 13) (100 . "AcDbSpline") (70 . 0) (71 . 3) (72 .
12) (73 . 8) (74 . 0) (42 . 0.0000001) (43 . 0.0000001) (40 . 0.0) (40 . 0.0) (40 . 0.0) (40 . 0.0) (40 . 0.3795845098)
(40 . 0.512161146) (40 . 0.6617670564) (40 . 0.7792397022) (40 . 1) (40 . 1) (40 . 1) (40 . 1) (10 6809.9547511312
369.5333710407 0.0) (10 6829.8569560374 380.5968518769 0.0) (10 6825.4891038121 415.3796337613 0.0) (10 6854.7123798282
434.388736946 0.0) (10 6870.1847146626 454.3889715878 0.0) (10 6893.0303374457 453.4870321648 0.0) (10 6901.7014935132
427.2485308744 0.0) (10 6915.5351809955 433.6340497737 0.0))
((0 . "LWPOLYLINE") (100 . "AcDbEntity") (8 . "PLANTS") (62 . 94) (370 . 13) (100 . "AcDbPolyline") (90 . 3) (70 . 0)
(43 . 0.0) (10 6858.9740950226 328.0542986425) (10 6832.5791855204 316.8904977376) (10 6809.9547511312 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6870.2863122172 6979.6380090498 0.0) (10 6844.9293006525 6966.6813253295 0.0) (10 6841.122808002
7000.0254650061 0.0) (10 6821.2669683258 6998.4919683258 0.0))
((0 . "LWPOLYLINE") (100 . "AcDbEntity") (8 . "PLANTS") (62 . 94) (370 . 13) (100 . "AcDbPolyline") (90 . 3) (70 . 0)
(43 . 0.0) (10 6873.1945783057 3895.4932453494) (10 6843.8914027149 3906.3376696833) (10 6821.2669683258
3906.4860859729))
((0 . "LWPOLYLINE") (100 . "AcDbEntity") (8 . "PLANTS") (62 . 94) (370 . 13) (100 . "AcDbPolyline") (90 . 2) (70 . 0)
(43 . 0.0) (10 6847.9298085386 3794.4341662813) (10 6825.0374434389 3795.2488687783))
((0 . "LWPOLYLINE") (100 . "AcDbEntity") (8 . "PLANTS") (62 . 94) (370 . 13) (100 . "AcDbPolyline") (90 . 2) (70 . 0)
(43 . 0.0) (10 6828.8087104072 6926.84739819) (10 6843.8914027149 6926.84739819))
((0 . "LWPOLYLINE") (100 . "AcDbEntity") (8 . "PLANTS") (62 . 94) (370 . 13) (100 . "AcDbPolyline") (90 . 3) (70 . 0)
(43 . 0.0) (10 6855.2036199095 6900.4524886878) (10 6848.859841629 6904.3778280543) (10 6843.8914027149 6926.84739819))
((0 . "LWPOLYLINE") (100 . "AcDbEntity") (8 . "PLANTS") (62 . 94) (370 . 13) (100 . "AcDbPolyline") (90 . 3) (70 . 0)
(43 . 0.0) (10 6881.5985294118 6938.1596153846) (10 6866.5158371041 6937.1101809955) (10 6843.8914027149 6926.84739819))
((0 . "LWPOLYLINE") (100 . "AcDbEntity") (8 . "PLANTS") (62 . 94) (370 . 13) (100 . "AcDbPolyline") (90 . 3) (70 . 0)
(43 . 0.0) (10 6855.2036199095 6900.4524886878) (10 6860.0305429864 6885.3697963801) (10 6870.2863122172
6874.0575791855))
((0 . "LWPOLYLINE") (100 . "AcDbEntity") (8 . "PLANTS") (62 . 94) (370 . 13) (100 . "AcDbPolyline") (90 . 3) (70 . 0)
(43 . 0.0) (10 6855.2036199095 6900.4524886878) (10 6862.7515837104 6906.7964932127) (10 6881.5985294118
6911.7647058824))
((0 . "LWPOLYLINE") (100 . "AcDbEntity") (8 . "PLANTS") (62 . 94) (370 . 13) (100 . "AcDbPolyline") (90 . 3) (70 . 0)
(43 . 0.0) (10 6855.2036199095 6840.1209276018) (10 6862.5976244344 6821.2669683258) (10 6862.745361991
6776.0180995475))
((0 . "LWPOLYLINE") (100 . "AcDbEntity") (8 . "PLANTS") (62 . 94) (370 . 13) (100 . "AcDbPolyline") (90 . 3) (70 . 0)
(43 . 0.0) (10 6855.2036199095 6840.1209276018) (10 6869.2299773756 6862.7450226244) (10 6870.2863122172
6874.0575791855))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6858.9740950226 6689.2908371041 0.0) (10 6853.9463990816 6677.5440283731 0.0) (10 6835.1938874726
6647.1741286934 0.0) (10 6855.2036199095 6636.5010180995 0.0))
((0 . "LWPOLYLINE") (100 . "AcDbEntity") (8 . "PLANTS") (62 . 94) (370 . 13) (100 . "AcDbPolyline") (90 . 3) (70 . 0)
(43 . 0.0) (10 6889.1402714932 328.0542986425) (10 6877.8280542986 324.2907239819) (10 6858.9740950226 328.0542986425))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6870.2863122172 414.782239819 0.0) (10 6876.3616804617 382.7769671737 0.0) (10 6826.4697316517
366.5705149502 0.0) (10 6858.9740950226 328.0542986425 0.0))
((0 . "LWPOLYLINE") (100 . "AcDbEntity") (8 . "PLANTS") (62 . 94) (370 . 13) (100 . "AcDbPolyline") (90 . 2) (70 . 0)
(43 . 0.0) (10 6862.745361991 6776.0180995475) (10 6870.2863122172 6776.0180995475))
((0 . "LWPOLYLINE") (100 . "AcDbEntity") (8 . "PLANTS") (62 . 94) (370 . 13) (100 . "AcDbPolyline") (90 . 3) (70 . 0)
(43 . 0.0) (10 6866.5158371041 6557.3154977376) (10 6862.745361991 6549.7737556561) (10 6866.5158371041
6542.2320135747))
((0 . "LWPOLYLINE") (100 . "AcDbEntity") (8 . "PLANTS") (62 . 94) (370 . 13) (100 . "AcDbPolyline") (90 . 2) (70 . 0)
(43 . 0.0) (10 6870.2863122172 6534.6910633484) (10 6866.5158371041 6542.2320135747))
((0 . "LWPOLYLINE") (100 . "AcDbEntity") (8 . "PLANTS") (62 . 94) (370 . 13) (100 . "AcDbPolyline") (90 . 2) (70 . 0)
(43 . 0.0) (10 6919.3064479638 6568.6277149321) (10 6866.5158371041 6542.2320135747))
((0 . "LWPOLYLINE") (100 . "AcDbEntity") (8 . "PLANTS") (62 . 94) (370 . 13) (100 . "AcDbPolyline") (90 . 2) (70 . 0)
(43 . 0.0) (10 6870.2863122172 6979.6380090498) (10 6885.3697963801 6945.7013574661))
((0 . "LWPOLYLINE") (100 . "AcDbEntity") (8 . "PLANTS") (62 . 94) (370 . 13) (100 . "AcDbPolyline") (90 . 2) (70 . 0)
(43 . 0.0) (10 6870.2863122172 6979.6380090498) (10 6885.3697963801 6998.4919683258))
((0 . "LWPOLYLINE") (100 . "AcDbEntity") (8 . "PLANTS") (62 . 94) (370 . 13) (100 . "AcDbPolyline") (90 . 3) (70 . 0)
(43 . 0.0) (10 6870.2863122172 6874.0575791855) (10 6889.1333710407 6875.2550904977) (10 6896.6820135747
6881.5985294118))
((0 . "LWPOLYLINE") (100 . "AcDbEntity") (8 . "PLANTS") (62 . 94) (370 . 13) (100 . "AcDbPolyline") (90 . 2) (70 . 0)
(43 . 0.0) (10 6870.2863122172 6730.7692307692) (10 6870.2863122172 6776.0180995475))
((0 . "LWPOLYLINE") (100 . "AcDbEntity") (8 . "PLANTS") (62 . 94) (370 . 13) (100 . "AcDbPolyline") (90 . 2) (70 . 0)
(43 . 0.0) (10 6911.7647058824 6779.7885746606) (10 6870.2863122172 6776.0180995475))
((0 . "LWPOLYLINE") (100 . "AcDbEntity") (8 . "PLANTS") (62 . 94) (370 . 13) (100 . "AcDbPolyline") (90 . 2) (70 . 0)
(43 . 0.0) (10 6911.7647058824 6730.7692307692) (10 6870.2863122172 6730.7692307692))
((0 . "LWPOLYLINE") (100 . "AcDbEntity") (8 . "PLANTS") (62 . 94) (370 . 13) (100 . "AcDbPolyline") (90 . 3) (70 . 0)
(43 . 0.0) (10 6877.8280542986 6417.7979638009) (10 6874.0575791855 6417.7979638009) (10 6870.2863122172
6410.2563348416))
((0 . "LWPOLYLINE") (100 . "AcDbEntity") (8 . "PLANTS") (62 . 94) (370 . 13) (100 . "AcDbPolyline") (90 . 3) (70 . 0)
(43 . 0.0) (10 6915.5351809955 6606.334841629) (10 6896.6820135747 6601.3600678733) (10 6877.8280542986
6583.7104072398))
((0 . "LWPOLYLINE") (100 . "AcDbEntity") (8 . "PLANTS") (62 . 94) (370 . 13) (100 . "AcDbPolyline") (90 . 2) (70 . 0)
(43 . 0.0) (10 6877.8280542986 6417.7979638009) (10 6885.3697963801 6417.7979638009))
((0 . "LWPOLYLINE") (100 . "AcDbEntity") (8 . "PLANTS") (62 . 94) (370 . 13) (100 . "AcDbPolyline") (90 . 2) (70 . 0)
(43 . 0.0) (10 6877.8280542986 6417.7979638009) (10 6885.3697963801 6440.42239819))
((0 . "LWPOLYLINE") (100 . "AcDbEntity") (8 . "PLANTS") (62 . 94) (370 . 13) (100 . "AcDbPolyline") (90 . 2) (70 . 0)
(43 . 0.0) (10 6881.5985294118 6938.1596153846) (10 6881.5985294118 6911.7647058824))
((0 . "LWPOLYLINE") (100 . "AcDbEntity") (8 . "PLANTS") (62 . 94) (370 . 13) (100 . "AcDbPolyline") (90 . 2) (70 . 0)
(43 . 0.0) (10 6881.5985294118 6938.1596153846) (10 6885.3697963801 6945.7013574661))
((0 . "LWPOLYLINE") (100 . "AcDbEntity") (8 . "PLANTS") (62 . 94) (370 . 13) (100 . "AcDbPolyline") (90 . 2) (70 . 0)
(43 . 0.0) (10 6881.5985294118 6911.7647058824) (10 6896.6820135747 6881.5985294118))
((0 . "LWPOLYLINE") (100 . "AcDbEntity") (8 . "PLANTS") (62 . 94) (370 . 13) (100 . "AcDbPolyline") (90 . 3) (70 . 0)
(43 . 0.0) (10 6881.5985294118 486.4253393665) (10 6882.7964932127 493.9726244344) (10 6890.9367259845 506.1393462963))
((0 . "LWPOLYLINE") (100 . "AcDbEntity") (8 . "PLANTS") (62 . 94) (370 . 13) (100 . "AcDbPolyline") (90 . 3) (70 . 0)
(43 . 0.0) (10 6885.3697963801 6998.4919683258) (10 6896.5334841629 6994.5662895928) (10 6923.0769230769
6960.7840497738))
((0 . "LWPOLYLINE") (100 . "AcDbEntity") (8 . "PLANTS") (62 . 94) (370 . 13) (100 . "AcDbPolyline") (90 . 2) (70 . 0)
(43 . 0.0) (10 6923.0769230769 6949.4718325792) (10 6885.3697963801 6945.7013574661))
((0 . "LWPOLYLINE") (100 . "AcDbEntity") (8 . "PLANTS") (62 . 94) (370 . 13) (100 . "AcDbPolyline") (90 . 2) (70 . 0)
(43 . 0.0) (10 6904.2229638009 305.4298642534) (10 6889.1402714932 328.0542986425))
((0 . "LWPOLYLINE") (100 . "AcDbEntity") (8 . "PLANTS") (62 . 94) (370 . 13) (100 . "AcDbPolyline") (90 . 3) (70 . 0)
(43 . 0.0) (10 6889.1402714932 328.0542986425) (10 6893.0653846154 369.5333710407) (10 6900.4524886878 384.6153846154))
((0 . "LWPOLYLINE") (100 . "AcDbEntity") (8 . "PLANTS") (62 . 94) (370 . 13) (100 . "AcDbPolyline") (90 . 3) (70 . 0)
(43 . 0.0) (10 6892.9107466063 7081.4479638009) (10 6899.2545248869 7055.0530542986) (10 6896.6820135747
7043.7408371041))
((0 . "LWPOLYLINE") (100 . "AcDbEntity") (8 . "PLANTS") (62 . 94) (370 . 13) (100 . "AcDbPolyline") (90 . 2) (70 . 0)
(43 . 0.0) (10 6915.5351809955 6628.9592760181) (10 6892.9107466063 6644.0419683258))
((0 . "LWPOLYLINE") (100 . "AcDbEntity") (8 . "PLANTS") (62 . 94) (370 . 13) (100 . "AcDbPolyline") (90 . 2) (70 . 0)
(43 . 0.0) (10 6892.9107466063 395.92760181) (10 6900.4524886878 384.6153846154))
((0 . "LWPOLYLINE") (100 . "AcDbEntity") (8 . "PLANTS") (62 . 94) (370 . 13) (100 . "AcDbPolyline") (90 . 2) (70 . 0)
(43 . 0.0) (10 6896.6820135747 6881.5985294118) (10 6934.3891402715 6881.5985294118))
((0 . "LWPOLYLINE") (100 . "AcDbEntity") (8 . "PLANTS") (62 . 94) (370 . 13) (100 . "AcDbPolyline") (90 . 2) (70 . 0)
(43 . 0.0) (10 6896.6820135747 6685.520361991) (10 6911.7647058824 6693.0621040724))
((0 . "LWPOLYLINE") (100 . "AcDbEntity") (8 . "PLANTS") (62 . 94) (370 . 13) (100 . "AcDbPolyline") (90 . 3) (70 . 0)
(43 . 0.0) (10 6900.4524886878 6298.3910633484) (10 6911.7584841629 6311.0085972851) (10 6919.3064479638
6312.2171945701))
((0 . "LWPOLYLINE") (100 . "AcDbEntity") (8 . "PLANTS") (62 . 94) (370 . 13) (100 . "AcDbPolyline") (90 . 2) (70 . 0)
(43 . 0.0) (10 6926.84739819 388.3851809955) (10 6900.4524886878 384.6153846154))
((0 . "LWPOLYLINE") (100 . "AcDbEntity") (8 . "PLANTS") (62 . 94) (370 . 13) (100 . "AcDbPolyline") (90 . 3) (70 . 0)
(43 . 0.0) (10 6907.9942307692 256.411199095) (10 6900.6071266968 267.7234162896) (10 6904.2229638009 305.4298642534))
((0 . "LWPOLYLINE") (100 . "AcDbEntity") (8 . "PLANTS") (62 . 94) (370 . 13) (100 . "AcDbPolyline") (90 . 2) (70 . 0)
(43 . 0.0) (10 6938.1596153846 316.742081448) (10 6904.2229638009 305.4298642534))
((0 . "LWPOLYLINE") (100 . "AcDbEntity") (8 . "PLANTS") (62 . 94) (370 . 13) (100 . "AcDbPolyline") (90 . 2) (70 . 0)
(43 . 0.0) (10 6907.9942307692 256.411199095) (10 6915.5351809955 256.411199095))
((0 . "LWPOLYLINE") (100 . "AcDbEntity") (8 . "PLANTS") (62 . 94) (370 . 13) (100 . "AcDbPolyline") (90 . 2) (70 . 0)
(43 . 0.0) (10 6911.7647058824 6779.7885746606) (10 6915.5351809955 6772.2476244344))
((0 . "LWPOLYLINE") (100 . "AcDbEntity") (8 . "PLANTS") (62 . 94) (370 . 13) (100 . "AcDbPolyline") (90 . 3) (70 . 0)
(43 . 0.0) (10 6923.0769230769 6828.8087104072) (10 6911.9124434389 6802.4130090498) (10 6911.7647058824
6779.7885746606))
((0 . "LWPOLYLINE") (100 . "AcDbEntity") (8 . "PLANTS") (62 . 94) (370 . 13) (100 . "AcDbPolyline") (90 . 2) (70 . 0)
(43 . 0.0) (10 6911.7647058824 6730.7692307692) (10 6911.7647058824 6693.0621040724))
((0 . "LWPOLYLINE") (100 . "AcDbEntity") (8 . "PLANTS") (62 . 94) (370 . 13) (100 . "AcDbPolyline") (90 . 2) (70 . 0)
(43 . 0.0) (10 6911.7647058824 6730.7692307692) (10 6915.5351809955 6738.3109728507))
((0 . "LWPOLYLINE") (100 . "AcDbEntity") (8 . "PLANTS") (62 . 94) (370 . 13) (100 . "AcDbPolyline") (90 . 2) (70 . 0)
(43 . 0.0) (10 6919.3064479638 6693.0621040724) (10 6911.7647058824 6693.0621040724))
((0 . "LWPOLYLINE") (100 . "AcDbEntity") (8 . "PLANTS") (62 . 94) (370 . 13) (100 . "AcDbPolyline") (90 . 2) (70 . 0)
(43 . 0.0) (10 6953.2430995475 6772.2476244344) (10 6915.5351809955 6772.2476244344))
((0 . "LWPOLYLINE") (100 . "AcDbEntity") (8 . "PLANTS") (62 . 94) (370 . 13) (100 . "AcDbPolyline") (90 . 2) (70 . 0)
(43 . 0.0) (10 6915.5351809955 6738.3109728507) (10 6915.5351809955 6772.2476244344))
((0 . "LWPOLYLINE") (100 . "AcDbEntity") (8 . "PLANTS") (62 . 94) (370 . 13) (100 . "AcDbPolyline") (90 . 2) (70 . 0)
(43 . 0.0) (10 6958.8992081448 6738.3109728507) (10 6915.5351809955 6738.3109728507))
((0 . "LWPOLYLINE") (100 . "AcDbEntity") (8 . "PLANTS") (62 . 94) (370 . 13) (100 . "AcDbPolyline") (90 . 2) (70 . 0)
(43 . 0.0) (10 6915.5351809955 6606.334841629) (10 6915.5351809955 6628.9592760181))
((0 . "LWPOLYLINE") (100 . "AcDbEntity") (8 . "PLANTS") (62 . 94) (370 . 13) (100 . "AcDbPolyline") (90 . 3) (70 . 0)
(43 . 0.0) (10 6930.6186651584 6655.3541855204) (10 6925.6495475113 6640.2714932127) (10 6915.5351809955
6628.9592760181))
((0 . "LWPOLYLINE") (100 . "AcDbEntity") (8 . "PLANTS") (62 . 94) (370 . 13) (100 . "AcDbPolyline") (90 . 3) (70 . 0)
(43 . 0.0) (10 6915.5351809955 6606.334841629) (10 6919.3064479638 6606.334841629) (10 6919.3064479638 6602.5643665158))
((0 . "LWPOLYLINE") (100 . "AcDbEntity") (8 . "PLANTS") (62 . 94) (370 . 13) (100 . "AcDbPolyline") (90 . 2) (70 . 0)
(43 . 0.0) (10 6915.5351809955 6606.334841629) (10 6919.3064479638 6602.5643665158))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6915.5351809955 256.411199095 0.0) (10 6921.5824819093 233.0043830597 0.0) (10 6965.2395049781
241.4237302954 0.0) (10 6975.8675339367 241.3263574661 0.0))
((0 . "LWPOLYLINE") (100 . "AcDbEntity") (8 . "PLANTS") (62 . 94) (370 . 13) (100 . "AcDbPolyline") (90 . 2) (70 . 0)
(43 . 0.0) (10 6945.7013574661 286.5752262443) (10 6915.5351809955 256.411199095))
((0 . "LWPOLYLINE") (100 . "AcDbEntity") (8 . "PLANTS") (62 . 94) (370 . 13) (100 . "AcDbPolyline") (90 . 2) (70 . 0)
(43 . 0.0) (10 6949.4718325792 6689.2908371041) (10 6919.3064479638 6693.0621040724))
((0 . "LWPOLYLINE") (100 . "AcDbEntity") (8 . "PLANTS") (62 . 94) (370 . 13) (100 . "AcDbPolyline") (90 . 3) (70 . 0)
(43 . 0.0) (10 6919.3064479638 6693.0621040724) (10 6920.3558823529 6677.9786199095) (10 6930.6186651584
6655.3541855204))
((0 . "LWPOLYLINE") (100 . "AcDbEntity") (8 . "PLANTS") (62 . 94) (370 . 13) (100 . "AcDbPolyline") (90 . 2) (70 . 0)
(43 . 0.0) (10 6919.3064479638 6602.5643665158) (10 6953.2430995475 6602.5643665158))
((0 . "LWPOLYLINE") (100 . "AcDbEntity") (8 . "PLANTS") (62 . 94) (370 . 13) (100 . "AcDbPolyline") (90 . 3) (70 . 0)
(43 . 0.0) (10 6919.3064479638 6568.6277149321) (10 6915.542081448 6583.7104072398) (10 6919.3064479638
6602.5643665158))
((0 . "LWPOLYLINE") (100 . "AcDbEntity") (8 . "PLANTS") (62 . 94) (370 . 13) (100 . "AcDbPolyline") (90 . 3) (70 . 0)
(43 . 0.0) (10 6919.3064479638 6568.6277149321) (10 6929.568438914 6553.5442307692) (10 6934.3891402715
6534.6910633484))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6919.3064479638 6312.2171945702 0.0) (10 6943.8406642074 6302.9267935392 0.0) (10 6915.4737617685
6279.3854100992 0.0) (10 6926.84739819 6263.1975113122 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6926.84739819 6387.6319004525 0.0) (10 6912.5332137241 6365.2802255454 0.0) (10 6930.2429677271
6336.1949523553 0.0) (10 6919.3064479638 6312.2171945701 0.0))
((0 . "LWPOLYLINE") (100 . "AcDbEntity") (8 . "PLANTS") (62 . 94) (370 . 13) (100 . "AcDbPolyline") (90 . 2) (70 . 0)
(43 . 0.0) (10 6923.0769230769 6949.4718325792) (10 6923.0769230769 6960.7840497738))
((0 . "LWPOLYLINE") (100 . "AcDbEntity") (8 . "PLANTS") (62 . 94) (370 . 13) (100 . "AcDbPolyline") (90 . 3) (70 . 0)
(43 . 0.0) (10 6941.9308823529 7006.032918552) (10 6937.103280543 6979.6380090498) (10 6923.0769230769 6960.7840497738))
((0 . "LWPOLYLINE") (100 . "AcDbEntity") (8 . "PLANTS") (62 . 94) (370 . 13) (100 . "AcDbPolyline") (90 . 2) (70 . 0)
(43 . 0.0) (10 6938.1596153846 6945.7013574661) (10 6923.0769230769 6949.4718325792))
((0 . "LWPOLYLINE") (100 . "AcDbEntity") (8 . "PLANTS") (62 . 94) (370 . 13) (100 . "AcDbPolyline") (90 . 3) (70 . 0)
(43 . 0.0) (10 6924.9625565611 6478.129638009) (10 6920.5042986425 6444.1929864253) (10 6923.0769230769
6406.4857466063))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6924.9625565611 6478.129638009 0.0) (10 6913.2738881863 6495.0634207844 0.0) (10 6907.9994856887
6524.476620106 0.0) (10 6934.3891402715 6534.6910633484 0.0))
((0 . "LWPOLYLINE") (100 . "AcDbEntity") (8 . "PLANTS") (62 . 94) (370 . 13) (100 . "AcDbPolyline") (90 . 3) (70 . 0)
(43 . 0.0) (10 7044.7289741117 6481.8938914027) (10 6960.7840497738 6481.8938914027) (10 6924.9625565611
6478.129638009))
((0 . "LWPOLYLINE") (100 . "AcDbEntity") (8 . "PLANTS") (62 . 94) (370 . 13) (100 . "AcDbPolyline") (90 . 2) (70 . 0)
(43 . 0.0) (10 6926.84739819 6240.5730769231) (10 6926.84739819 6217.9486425339))
((0 . "LWPOLYLINE") (100 . "AcDbEntity") (8 . "PLANTS") (62 . 94) (370 . 13) (100 . "AcDbPolyline") (90 . 3) (70 . 0)
(43 . 0.0) (10 6926.84739819 388.3851809955) (10 6934.5375565611 377.228280543) (10 6949.4718325792 369.5333710407))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6926.84739819 388.3851809955 0.0) (10 6928.6164328412 407.1852193749 0.0) (10 6951.0788133266
418.6765261529 0.0) (10 6968.3257918552 414.782239819 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6949.4718325792 6689.2908371041 0.0) (10 6960.5330868305 6675.7853311847 0.0) (10 6952.1384319087
6647.5382185365 0.0) (10 6930.6186651584 6655.3541855204 0.0))
((0 . "LWPOLYLINE") (100 . "AcDbEntity") (8 . "PLANTS") (62 . 94) (370 . 13) (100 . "AcDbPolyline") (90 . 3) (70 . 0)
(43 . 0.0) (10 6953.2430995475 7096.5306561086) (10 6941.9308823529 7111.3109728507) (10 6934.3891402715
7111.6141402715))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6934.3891402715 7043.7408371041 0.0) (10 6916.6347474699 7039.1940597509 0.0) (10 6927.6456977191
7007.7183863826 0.0) (10 6941.9308823529 7006.032918552 0.0))
((0 . "LWPOLYLINE") (100 . "AcDbEntity") (8 . "PLANTS") (62 . 94) (370 . 13) (100 . "AcDbPolyline") (90 . 2) (70 . 0)
(43 . 0.0) (10 6953.2430995475 6881.5985294118) (10 6934.3891402715 6881.5985294118))
((0 . "LWPOLYLINE") (100 . "AcDbEntity") (8 . "PLANTS") (62 . 94) (370 . 13) (100 . "AcDbPolyline") (90 . 3) (70 . 0)
(43 . 0.0) (10 6938.1596153846 6945.7013574661) (10 6938.0118778281 6896.6820135747) (10 6934.3891402715
6881.5985294118))
((0 . "LWPOLYLINE") (100 . "AcDbEntity") (8 . "PLANTS") (62 . 94) (370 . 13) (100 . "AcDbPolyline") (90 . 3) (70 . 0)
(43 . 0.0) (10 6934.3891402715 6534.6910633484) (10 6949.4656108597 6530.7653846154) (10 6964.5553167421
6512.0662895928))
((0 . "LWPOLYLINE") (100 . "AcDbEntity") (8 . "PLANTS") (62 . 94) (370 . 13) (100 . "AcDbPolyline") (90 . 2) (70 . 0)
(43 . 0.0) (10 6938.1596153846 6945.7013574661) (10 6960.7840497738 6945.7013574661))
((0 . "LWPOLYLINE") (100 . "AcDbEntity") (8 . "PLANTS") (62 . 94) (370 . 13) (100 . "AcDbPolyline") (90 . 3) (70 . 0)
(43 . 0.0) (10 6938.1596153846 316.742081448) (10 6945.546719457 305.4298642534) (10 6945.7013574661 286.5752262443))
((0 . "LWPOLYLINE") (100 . "AcDbEntity") (8 . "PLANTS") (62 . 94) (370 . 13) (100 . "AcDbPolyline") (90 . 3) (70 . 0)
(43 . 0.0) (10 6938.1596153846 316.742081448) (10 6945.7013574661 326.8494343891) (10 6953.2430995475 328.0542986425))
((0 . "LWPOLYLINE") (100 . "AcDbEntity") (8 . "PLANTS") (62 . 94) (370 . 13) (100 . "AcDbPolyline") (90 . 3) (70 . 0)
(43 . 0.0) (10 6968.3257918552 7043.7408371041) (10 6955.957239819 7013.5812217195) (10 6941.9308823529 7006.032918552))
((0 . "LWPOLYLINE") (100 . "AcDbEntity") (8 . "PLANTS") (62 . 94) (370 . 13) (100 . "AcDbPolyline") (90 . 3) (70 . 0)
(43 . 0.0) (10 6987.9337104072 294.8716063348) (10 6968.3257918552 286.7236425339) (10 6945.7013574661 286.5752262443))
((0 . "LWPOLYLINE") (100 . "AcDbEntity") (8 . "PLANTS") (62 . 94) (370 . 13) (100 . "AcDbPolyline") (90 . 3) (70 . 0)
(43 . 0.0) (10 6949.4718325792 6689.2908371041) (10 6960.6363122172 6719.4570135747) (10 6958.8992081448
6738.3109728507))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6952.5849058821 528.8518336269 0.0) (10 6978.5170574002 501.5471825041 0.0) (10 7022.0082632804
499.3242875889 0.0) (10 7047.5113122172 471.3433257919 0.0))
((0 . "LWPOLYLINE") (100 . "AcDbEntity") (8 . "PLANTS") (62 . 94) (370 . 13) (100 . "AcDbPolyline") (90 . 2) (70 . 0)
(43 . 0.0) (10 6953.2430995475 328.0542986425) (10 6949.4718325792 369.5333710407))
((0 . "LWPOLYLINE") (100 . "AcDbEntity") (8 . "PLANTS") (62 . 94) (370 . 13) (100 . "AcDbPolyline") (90 . 2) (70 . 0)
(43 . 0.0) (10 6968.3257918552 377.0729638009) (10 6949.4718325792 369.5333710407))
((0 . "LWPOLYLINE") (100 . "AcDbEntity") (8 . "PLANTS") (62 . 94) (370 . 13) (100 . "AcDbPolyline") (90 . 2) (70 . 0)
(43 . 0.0) (10 6953.2430995475 6881.5985294118) (10 6957.0135746606 6862.745361991))
((0 . "LWPOLYLINE") (100 . "AcDbEntity") (8 . "PLANTS") (62 . 94) (370 . 13) (100 . "AcDbPolyline") (90 . 3) (70 . 0)
(43 . 0.0) (10 6953.2430995475 6881.5985294118) (10 6982.2106334842 6907.9942307692) (10 6987.1797511312
6930.6186651584))
((0 . "LWPOLYLINE") (100 . "AcDbEntity") (8 . "PLANTS") (62 . 94) (370 . 13) (100 . "AcDbPolyline") (90 . 3) (70 . 0)
(43 . 0.0) (10 6953.2430995475 6772.2476244344) (10 6953.3942307692 6749.6231900452) (10 6958.8992081448
6738.3109728507))
((0 . "LWPOLYLINE") (100 . "AcDbEntity") (8 . "PLANTS") (62 . 94) (370 . 13) (100 . "AcDbPolyline") (90 . 2) (70 . 0)
(43 . 0.0) (10 6964.5553167421 6779.7885746606) (10 6953.2430995475 6772.2476244344))
((0 . "LWPOLYLINE") (100 . "AcDbEntity") (8 . "PLANTS") (62 . 94) (370 . 13) (100 . "AcDbPolyline") (90 . 2) (70 . 0)
(43 . 0.0) (10 6960.7840497738 6576.1686651584) (10 6953.2430995475 6602.5643665158))
((0 . "LWPOLYLINE") (100 . "AcDbEntity") (8 . "PLANTS") (62 . 94) (370 . 13) (100 . "AcDbPolyline") (90 . 2) (70 . 0)
(43 . 0.0) (10 6957.0135746606 6613.8765837104) (10 6953.2430995475 6602.5643665158))
((0 . "LWPOLYLINE") (100 . "AcDbEntity") (8 . "PLANTS") (62 . 94) (370 . 13) (100 . "AcDbPolyline") (90 . 2) (70 . 0)
(43 . 0.0) (10 6953.2430995475 6444.1929864253) (10 6972.0962669683 6398.9441176471))
((0 . "LWPOLYLINE") (100 . "AcDbEntity") (8 . "PLANTS") (62 . 94) (370 . 13) (100 . "AcDbPolyline") (90 . 2) (70 . 0)
(43 . 0.0) (10 6983.4084841629 328.0542986425) (10 6953.2430995475 328.0542986425))
((0 . "LWPOLYLINE") (100 . "AcDbEntity") (8 . "PLANTS") (62 . 94) (370 . 13) (100 . "AcDbPolyline") (90 . 2) (70 . 0)
(43 . 0.0) (10 6968.3257918552 7043.7408371041) (10 6957.0135746606 7073.9062217195))
((0 . "LWPOLYLINE") (100 . "AcDbEntity") (8 . "PLANTS") (62 . 94) (370 . 13) (100 . "AcDbPolyline") (90 . 3) (70 . 0)
(43 . 0.0) (10 7028.6573529412 6862.745361991) (10 7009.8041855204 6858.9740950226) (10 6957.0135746606 6862.745361991))
((0 . "LWPOLYLINE") (100 . "AcDbEntity") (8 . "PLANTS") (62 . 94) (370 . 13) (100 . "AcDbPolyline") (90 . 3) (70 . 0)
(43 . 0.0) (10 6964.5553167421 6779.7885746606) (10 6958.2107466063 6813.7252262443) (10 6957.0135746606
6862.745361991))
((0 . "LWPOLYLINE") (100 . "AcDbEntity") (8 . "PLANTS") (62 . 94) (370 . 13) (100 . "AcDbPolyline") (90 . 2) (70 . 0)
(43 . 0.0) (10 6983.4084841629 6742.0814479638) (10 6958.8992081448 6738.3109728507))
((0 . "LWPOLYLINE") (100 . "AcDbEntity") (8 . "PLANTS") (62 . 94) (370 . 13) (100 . "AcDbPolyline") (90 . 3) (70 . 0)
(43 . 0.0) (10 6960.7840497738 6945.7013574661) (10 6972.0962669683 6935.5933257919) (10 6987.1797511312
6930.6186651584))
((0 . "LWPOLYLINE") (100 . "AcDbEntity") (8 . "PLANTS") (62 . 94) (370 . 13) (100 . "AcDbPolyline") (90 . 3) (70 . 0)
(43 . 0.0) (10 6983.4084841629 6968.3257918552) (10 6972.0962669683 6960.7774886878) (10 6960.7840497738
6945.7013574661))
((0 . "LWPOLYLINE") (100 . "AcDbEntity") (8 . "PLANTS") (62 . 94) (370 . 13) (100 . "AcDbPolyline") (90 . 2) (70 . 0)
(43 . 0.0) (10 6964.5553167421 6779.7885746606) (10 6983.4084841629 6776.0180995475))
((0 . "LWPOLYLINE") (100 . "AcDbEntity") (8 . "PLANTS") (62 . 94) (370 . 13) (100 . "AcDbPolyline") (90 . 2) (70 . 0)
(43 . 0.0) (10 6998.4919683258 7039.9695701357) (10 6968.3257918552 7043.7408371041))
((0 . "LWPOLYLINE") (100 . "AcDbEntity") (8 . "PLANTS") (62 . 94) (370 . 13) (100 . "AcDbPolyline") (90 . 3) (70 . 0)
(43 . 0.0) (10 6968.3257918552 377.0729638009) (10 6971.8001131222 384.6222850679) (10 6968.3257918552 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 6968.3257918552 414.782239819 0.0) (10 6980.2380115489 434.9270802573 0.0) (10 7007.8580845279
459.6614855633 0.0) (10 7032.4286199095 444.9462669683 0.0))
((0 . "LWPOLYLINE") (100 . "AcDbEntity") (8 . "PLANTS") (62 . 94) (370 . 13) (100 . "AcDbPolyline") (90 . 3) (70 . 0)
(43 . 0.0) (10 6968.3257918552 377.0729638009) (10 6990.9537330317 368.4721719457) (10 7004.1480769231 356.334841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7039.9695701357 248.8687782805 0.0) (10 7026.3565772192 226.7578177886 0.0) (10 6994.639595439
227.7272869834 0.0) (10 6975.8675339367 241.3263574661 0.0))
((0 . "LWPOLYLINE") (100 . "AcDbEntity") (8 . "PLANTS") (62 . 94) (370 . 13) (100 . "AcDbPolyline") (90 . 2) (70 . 0)
(43 . 0.0) (10 6987.9337104072 294.8716063348) (10 6975.8675339367 241.3263574661))
((0 . "LWPOLYLINE") (100 . "AcDbEntity") (8 . "PLANTS") (62 . 94) (370 . 13) (100 . "AcDbPolyline") (90 . 2) (70 . 0)
(43 . 0.0) (10 6983.4084841629 6968.3257918552) (10 7006.032918552 6941.9308823529))
((0 . "LWPOLYLINE") (100 . "AcDbEntity") (8 . "PLANTS") (62 . 94) (370 . 13) (100 . "AcDbPolyline") (90 . 3) (70 . 0)
(43 . 0.0) (10 6983.4084841629 6968.3257918552) (10 6994.72760181 6985.9820135747) (10 7013.5746606335 6990.9502262443))
((0 . "LWPOLYLINE") (100 . "AcDbEntity") (8 . "PLANTS") (62 . 94) (370 . 13) (100 . "AcDbPolyline") (90 . 2) (70 . 0)
(43 . 0.0) (10 7043.7408371041 6776.0180995475) (10 6983.4084841629 6776.0180995475))
((0 . "LWPOLYLINE") (100 . "AcDbEntity") (8 . "PLANTS") (62 . 94) (370 . 13) (100 . "AcDbPolyline") (90 . 2) (70 . 0)
(43 . 0.0) (10 6983.4084841629 6742.0814479638) (10 6983.4084841629 6776.0180995475))
((0 . "LWPOLYLINE") (100 . "AcDbEntity") (8 . "PLANTS") (62 . 94) (370 . 13) (100 . "AcDbPolyline") (90 . 2) (70 . 0)
(43 . 0.0) (10 6983.4084841629 6742.0814479638) (10 7021.1164027149 6726.9987556561))
((0 . "LWPOLYLINE") (100 . "AcDbEntity") (8 . "PLANTS") (62 . 94) (370 . 13) (100 . "AcDbPolyline") (90 . 3) (70 . 0)
(43 . 0.0) (10 6987.9337104072 294.8716063348) (10 6983.5859728507 305.3173076923) (10 6983.4084841629 328.0542986425))
((0 . "LWPOLYLINE") (100 . "AcDbEntity") (8 . "PLANTS") (62 . 94) (370 . 13) (100 . "AcDbPolyline") (90 . 3) (70 . 0)
(43 . 0.0) (10 6983.4084841629 328.0542986425) (10 6992.0093891403 346.9047511312) (10 7004.1480769231 356.334841629))
((0 . "LWPOLYLINE") (100 . "AcDbEntity") (8 . "PLANTS") (62 . 94) (370 . 13) (100 . "AcDbPolyline") (90 . 3) (70 . 0)
(43 . 0.0) (10 7006.032918552 6941.9308823529) (10 6994.72760181 6931.8229638009) (10 6987.1797511312 6930.6186651584))
((0 . "LWPOLYLINE") (100 . "AcDbEntity") (8 . "PLANTS") (62 . 94) (370 . 13) (100 . "AcDbPolyline") (90 . 2) (70 . 0)
(43 . 0.0) (10 6987.1797511312 6625.188800905) (10 7021.1164027149 6598.7930995475))
((0 . "LWPOLYLINE") (100 . "AcDbEntity") (8 . "PLANTS") (62 . 94) (370 . 13) (100 . "AcDbPolyline") (90 . 3) (70 . 0)
(43 . 0.0) (10 6987.9337104072 294.8716063348) (10 7013.5746606335 276.4540723982) (10 7036.1990950226 267.7234162896))
((0 . "LWPOLYLINE") (100 . "AcDbEntity") (8 . "PLANTS") (62 . 94) (370 . 13) (100 . "AcDbPolyline") (90 . 3) (70 . 0)
(43 . 0.0) (10 6987.9337104072 294.8716063348) (10 7019.918438914 324.2845022624) (10 7024.8868778281 346.9089366516))
((0 . "LWPOLYLINE") (100 . "AcDbEntity") (8 . "PLANTS") (62 . 94) (370 . 13) (100 . "AcDbPolyline") (90 . 2) (70 . 0)
(43 . 0.0) (10 6994.7207013575 6685.520361991) (10 6998.4919683258 6677.9786199095))
((0 . "LWPOLYLINE") (100 . "AcDbEntity") (8 . "PLANTS") (62 . 94) (370 . 13) (100 . "AcDbPolyline") (90 . 2) (70 . 0)
(43 . 0.0) (10 6998.4919683258 7085.218438914) (10 7006.032918552 7077.6774886878))
((0 . "LWPOLYLINE") (100 . "AcDbEntity") (8 . "PLANTS") (62 . 94) (370 . 13) (100 . "AcDbPolyline") (90 . 2) (70 . 0)
(43 . 0.0) (10 6998.4919683258 7039.9695701357) (10 7013.5746606335 7017.3451357466))
((0 . "LWPOLYLINE") (100 . "AcDbEntity") (8 . "PLANTS") (62 . 94) (370 . 13) (100 . "AcDbPolyline") (90 . 2) (70 . 0)
(43 . 0.0) (10 6998.4919683258 7039.9695701357) (10 7006.032918552 7077.6774886878))
((0 . "LWPOLYLINE") (100 . "AcDbEntity") (8 . "PLANTS") (62 . 94) (370 . 13) (100 . "AcDbPolyline") (90 . 3) (70 . 0)
(43 . 0.0) (10 7004.1480769231 356.334841629) (10 7017.335520362 353.2554298643) (10 7024.8868778281 346.9089366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7004.1480769231 356.334841629 0.0) (10 6996.5274366908 391.1759258055 0.0) (10 7033.2320747182
411.5526501814 0.0) (10 7032.4286199095 444.9462669683 0.0))
((0 . "LWPOLYLINE") (100 . "AcDbEntity") (8 . "PLANTS") (62 . 94) (370 . 13) (100 . "AcDbPolyline") (90 . 2) (70 . 0)
(43 . 0.0) (10 7036.1990950226 7081.4479638009) (10 7006.032918552 7077.6774886878))
((0 . "LWPOLYLINE") (100 . "AcDbEntity") (8 . "PLANTS") (62 . 94) (370 . 13) (100 . "AcDbPolyline") (90 . 2) (70 . 0)
(43 . 0.0) (10 7036.1990950226 6941.9308823529) (10 7006.032918552 6941.9308823529))
((0 . "LWPOLYLINE") (100 . "AcDbEntity") (8 . "PLANTS") (62 . 94) (370 . 13) (100 . "AcDbPolyline") (90 . 2) (70 . 0)
(43 . 0.0) (10 7013.5746606335 7017.3451357466) (10 7013.5746606335 6990.9502262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7036.1990950226 7081.4479638009 0.0) (10 7049.3973415388 7059.6208163765 0.0) (10 7044.2050003316
7022.3838420604 0.0) (10 7013.5746606335 7017.3451357466 0.0))
((0 . "LWPOLYLINE") (100 . "AcDbEntity") (8 . "PLANTS") (62 . 94) (370 . 13) (100 . "AcDbPolyline") (90 . 2) (70 . 0)
(43 . 0.0) (10 7036.1990950226 6987.1797511312) (10 7013.5746606335 6990.9502262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7055.5351525046 6591.7567050637 0.0) (10 7046.5597753068 6603.6077690187 0.0) (10 7025.1395896625
6581.1573604734 0.0) (10 7021.1164027149 6598.7930995475 0.0))
((0 . "LWPOLYLINE") (100 . "AcDbEntity") (8 . "PLANTS") (62 . 94) (370 . 13) (100 . "AcDbPolyline") (90 . 2) (70 . 0)
(43 . 0.0) (10 7036.1990950226 6613.8765837104) (10 7021.1164027149 6598.7930995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7134.2385746607 478.882918552 0.0) (10 7141.0554662423 550.328366815 0.0) (10 7050.3910778059
577.1515436919 0.0) (10 7024.8868778281 637.253959276 0.0))
((0 . "LWPOLYLINE") (100 . "AcDbEntity") (8 . "PLANTS") (62 . 94) (370 . 13) (100 . "AcDbPolyline") (90 . 3) (70 . 0)
(43 . 0.0) (10 7066.3652714932 309.1996606335) (10 7051.2755656109 335.4483031674) (10 7024.8868778281 346.9089366516))
((0 . "LWPOLYLINE") (100 . "AcDbEntity") (8 . "PLANTS") (62 . 94) (370 . 13) (100 . "AcDbPolyline") (90 . 3) (70 . 0)
(43 . 0.0) (10 7028.6573529412 6862.745361991) (10 7036.1990950226 6855.2036199095) (10 7043.7408371041
6855.2036199095))
((0 . "LWPOLYLINE") (100 . "AcDbEntity") (8 . "PLANTS") (62 . 94) (370 . 13) (100 . "AcDbPolyline") (90 . 3) (70 . 0)
(43 . 0.0) (10 7028.6573529412 6862.745361991) (10 7046.3202488688 6896.6820135747) (10 7051.2817873303
6915.5351809955))
((0 . "LWPOLYLINE") (100 . "AcDbEntity") (8 . "PLANTS") (62 . 94) (370 . 13) (100 . "AcDbPolyline") (90 . 3) (70 . 0)
(43 . 0.0) (10 7047.5113122172 471.3433257919) (10 7042.6843891403 452.6371040724) (10 7032.4286199095 444.9462669683))
((0 . "LWPOLYLINE") (100 . "AcDbEntity") (8 . "PLANTS") (62 . 94) (370 . 13) (100 . "AcDbPolyline") (90 . 2) (70 . 0)
(43 . 0.0) (10 7036.1990950226 7081.4479638009) (10 7036.1990950226 7100.3019230769))
((0 . "LWPOLYLINE") (100 . "AcDbEntity") (8 . "PLANTS") (62 . 94) (370 . 13) (100 . "AcDbPolyline") (90 . 2) (70 . 0)
(43 . 0.0) (10 7036.1990950226 6987.1797511312) (10 7036.1990950226 6957.0135746606))
((0 . "LWPOLYLINE") (100 . "AcDbEntity") (8 . "PLANTS") (62 . 94) (370 . 13) (100 . "AcDbPolyline") (90 . 3) (70 . 0)
(43 . 0.0) (10 7036.1990950226 6987.1797511312) (10 7062.5940045249 7008.5998868778) (10 7077.6774886878
7013.5746606335))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7107.8428733032 6919.3064479638 0.0) (10 7094.7123737163 6945.8983867191 0.0) (10 7064.8192546653
6962.2822858055 0.0) (10 7036.1990950226 6957.0135746606 0.0))
((0 . "LWPOLYLINE") (100 . "AcDbEntity") (8 . "PLANTS") (62 . 94) (370 . 13) (100 . "AcDbPolyline") (90 . 2) (70 . 0)
(43 . 0.0) (10 7036.1990950226 6941.9308823529) (10 7036.1990950226 6957.0135746606))
((0 . "LWPOLYLINE") (100 . "AcDbEntity") (8 . "PLANTS") (62 . 94) (370 . 13) (100 . "AcDbPolyline") (90 . 2) (70 . 0)
(43 . 0.0) (10 7036.1990950226 6941.9308823529) (10 7051.2817873303 6915.5351809955))
((0 . "LWPOLYLINE") (100 . "AcDbEntity") (8 . "PLANTS") (62 . 94) (370 . 13) (100 . "AcDbPolyline") (90 . 2) (70 . 0)
(43 . 0.0) (10 7039.9695701357 248.8687782805) (10 7036.1990950226 267.7234162896))
((0 . "LWPOLYLINE") (100 . "AcDbEntity") (8 . "PLANTS") (62 . 94) (370 . 13) (100 . "AcDbPolyline") (90 . 3) (70 . 0)
(43 . 0.0) (10 7066.3652714932 309.1996606335) (10 7048.5676470588 294.1176470588) (10 7036.1990950226 267.7234162896))
((0 . "LWPOLYLINE") (100 . "AcDbEntity") (8 . "PLANTS") (62 . 94) (370 . 13) (100 . "AcDbPolyline") (90 . 2) (70 . 0)
(43 . 0.0) (10 7043.7408371041 6776.0180995475) (10 7039.9695701357 6794.8720588235))
((0 . "LWPOLYLINE") (100 . "AcDbEntity") (8 . "PLANTS") (62 . 94) (370 . 13) (100 . "AcDbPolyline") (90 . 2) (70 . 0)
(43 . 0.0) (10 7039.9695701357 248.8687782805) (10 7062.5940045249 248.8687782805))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7107.8428733032 6843.8914027149 0.0) (10 7091.8325848139 6820.2806248164 0.0) (10 7048.905528027
6826.7808384032 0.0) (10 7043.7408371041 6855.2036199095 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7107.8428733032 6874.0575791855 0.0) (10 7085.2657137993 6882.2843541925 0.0) (10 7059.0753728006
6872.64052716 0.0) (10 7043.7408371041 6855.2036199095 0.0))
((0 . "LWPOLYLINE") (100 . "AcDbEntity") (8 . "PLANTS") (62 . 94) (370 . 13) (100 . "AcDbPolyline") (90 . 2) (70 . 0)
(43 . 0.0) (10 7043.7408371041 6776.0180995475) (10 7051.2817873303 6776.0180995475))
((0 . "LWPOLYLINE") (100 . "AcDbEntity") (8 . "PLANTS") (62 . 94) (370 . 13) (100 . "AcDbPolyline") (90 . 2) (70 . 0)
(43 . 0.0) (10 7051.2817873303 6655.3541855204) (10 7043.7408371041 6655.3541855204))
((0 . "LWPOLYLINE") (100 . "AcDbEntity") (8 . "PLANTS") (62 . 94) (370 . 13) (100 . "AcDbPolyline") (90 . 2) (70 . 0)
(43 . 0.0) (10 7130.4673076923 716.439479638) (10 7048.2595089701 727.649669678))
((0 . "LWPOLYLINE") (100 . "AcDbEntity") (8 . "PLANTS") (62 . 94) (370 . 13) (100 . "AcDbPolyline") (90 . 2) (70 . 0)
(43 . 0.0) (10 7077.6774886878 471.3433257919) (10 7047.5113122172 471.3433257919))
((0 . "LWPOLYLINE") (100 . "AcDbEntity") (8 . "PLANTS") (62 . 94) (370 . 13) (100 . "AcDbPolyline") (90 . 2) (70 . 0)
(43 . 0.0) (10 7051.2817873303 6915.5351809955) (10 7070.1357466063 6923.0769230769))
((0 . "LWPOLYLINE") (100 . "AcDbEntity") (8 . "PLANTS") (62 . 94) (370 . 13) (100 . "AcDbPolyline") (90 . 3) (70 . 0)
(43 . 0.0) (10 7062.5940045249 6738.3109728507) (10 7052.4859728507 6745.8588235294) (10 7051.2817873303
6776.0180995475))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7987766699) (40
. 1) (40 . 1) (40 . 1) (40 . 1) (10 7503.7704751131 6779.7885746606 0.0) (10 7383.8742037134 6776.2894633458 0.0) (10
7231.9234633446 6770.7916561353 0.0) (10 7080.9853193102 6785.6212123626 0.0) (10 7051.2817873303 6776.0180995475 0.0))
((0 . "LWPOLYLINE") (100 . "AcDbEntity") (8 . "PLANTS") (62 . 94) (370 . 13) (100 . "AcDbPolyline") (90 . 2) (70 . 0)
(43 . 0.0) (10 7061.0686835098 6648.0142702828) (10 7051.2817873303 6655.3541855204))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7051.2817873303 6655.3541855204 0.0) (10 7049.9490628527 6661.9912912159 0.0) (10 7049.2346655474
6691.2531233963 0.0) (10 7065.108557436 6689.0863218659 0.0))
((0 . "LWPOLYLINE") (100 . "AcDbEntity") (8 . "PLANTS") (62 . 94) (370 . 13) (100 . "AcDbPolyline") (90 . 3) (70 . 0)
(43 . 0.0) (10 7058.8235294118 384.6153846154) (10 7066.2236425339 380.6902714932) (10 7092.7601809955 346.9089366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7111.6141402715 241.3263574661 0.0) (10 7096.5944482789 232.2040533207 0.0) (10 7071.5576495026
230.757859143 0.0) (10 7062.5940045249 248.8687782805 0.0))
((0 . "LWPOLYLINE") (100 . "AcDbEntity") (8 . "PLANTS") (62 . 94) (370 . 13) (100 . "AcDbPolyline") (90 . 3) (70 . 0)
(43 . 0.0) (10 7085.218438914 294.1176470588) (10 7082.342760181 275.2630090498) (10 7062.5940045249 248.8687782805))
((0 . "LWPOLYLINE") (100 . "AcDbEntity") (8 . "PLANTS") (62 . 94) (370 . 13) (100 . "AcDbPolyline") (90 . 2) (70 . 0)
(43 . 0.0) (10 7085.218438914 294.1176470588) (10 7066.3652714932 309.1996606335))
((0 . "SPLINE") (100 . "AcDbEntity") (8 . "PLANTS") (62 . 94) (370 . 13) (100 . "AcDbSpline") (70 . 0) (71 . 3) (72 .
12) (73 . 8) (74 . 0) (42 . 0.0000001) (43 . 0.0000001) (40 . 0.0) (40 . 0.0) (40 . 0.0) (40 . 0.0) (40 . 0.292999149)
(40 . 0.3712449798) (40 . 0.6526373857) (40 . 0.9082157989) (40 . 1) (40 . 1) (40 . 1) (40 . 1) (10 7107.8428733032
6919.3064479638 0.0) (10 7113.3829417934 6937.8036611051 0.0) (10 7154.9281932201 6937.7260967054 0.0) (10
7152.6075795386 6982.3593822934 0.0) (10 7118.6986998922 7009.9185640294 0.0) (10 7087.182266119 7028.9139364185 0.0)
(10 7083.6412674435 7054.9907133659 0.0) (10 7073.9062217195 7047.5113122172 0.0))
((0 . "LWPOLYLINE") (100 . "AcDbEntity") (8 . "PLANTS") (62 . 94) (370 . 13) (100 . "AcDbPolyline") (90 . 2) (70 . 0)
(43 . 0.0) (10 7077.6774886878 788.0854072398) (10 7119.1550904977 784.3127828054))
((0 . "LWPOLYLINE") (100 . "AcDbEntity") (8 . "PLANTS") (62 . 94) (370 . 13) (100 . "AcDbPolyline") (90 . 2) (70 . 0)
(43 . 0.0) (10 7096.5306561086 456.2584841629) (10 7077.6774886878 471.3433257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7164.403959276 554.2986425339 0.0) (10 7148.2913197207 613.1838243008 0.0) (10 7075.8515389067
640.6076890267 0.0) (10 7030.8977095995 671.7060939283 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7008.5098248538 599.5673541921 0.0) (10 7016.6883035747 549.5002964324 0.0) (10 7079.1879881504
523.6729905178 0.0) (10 7077.6774886878 471.3433257918 0.0))
((0 . "LWPOLYLINE") (100 . "AcDbEntity") (8 . "PLANTS") (62 . 94) (370 . 13) (100 . "AcDbPolyline") (90 . 2) (70 . 0)
(43 . 0.0) (10 7085.218438914 825.7918552036) (10 7119.1550904977 825.7918552036))
((0 . "LWPOLYLINE") (100 . "AcDbEntity") (8 . "PLANTS") (62 . 94) (370 . 13) (100 . "AcDbPolyline") (90 . 2) (70 . 0)
(43 . 0.0) (10 7085.218438914 294.1176470588) (10 7104.07239819 305.4298642534))
((0 . "LWPOLYLINE") (100 . "AcDbEntity") (8 . "PLANTS") (62 . 94) (370 . 13) (100 . "AcDbPolyline") (90 . 3) (70 . 0)
(43 . 0.0) (10 7092.7601809955 346.9089366516) (10 7092.9148190045 328.0542986425) (10 7104.07239819 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7168.1752262444 309.1996606334 0.0) (10 7135.045249677 294.4724261011 0.0) (10 7128.7399439559
368.4140619282 0.0) (10 7092.7601809955 346.9089366516 0.0))
((0 . "LWPOLYLINE") (100 . "AcDbEntity") (8 . "PLANTS") (62 . 94) (370 . 13) (100 . "AcDbPolyline") (90 . 2) (70 . 0)
(43 . 0.0) (10 7096.5306561086 456.2584841629) (10 7122.9263574661 456.2584841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7168.1752262444 309.1996606335 0.0) (10 7168.6614874614 367.5347971582 0.0) (10 7096.2268549261
397.5598919195 0.0) (10 7096.5306561086 456.2584841629 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7160.6334841629 279.0356334842 0.0) (10 7136.8775195841 276.6436593001 0.0) (10 7126.2432579604
305.2219030185 0.0) (10 7104.07239819 305.4298642534 0.0))
((0 . "LWPOLYLINE") (100 . "AcDbEntity") (8 . "PLANTS") (62 . 94) (370 . 13) (100 . "AcDbPolyline") (90 . 3) (70 . 0)
(43 . 0.0) (10 7107.8428733032 6919.3064479638) (10 7107.9914027149 6900.4524886878) (10 7115.3846153846
6881.5985294118))
((0 . "LWPOLYLINE") (100 . "AcDbEntity") (8 . "PLANTS") (62 . 94) (370 . 13) (100 . "AcDbPolyline") (90 . 2) (70 . 0)
(43 . 0.0) (10 7107.8428733032 6874.0575791855) (10 7107.8428733032 6843.8914027149))
((0 . "LWPOLYLINE") (100 . "AcDbEntity") (8 . "PLANTS") (62 . 94) (370 . 13) (100 . "AcDbPolyline") (90 . 2) (70 . 0)
(43 . 0.0) (10 7115.3846153846 6881.5985294118) (10 7107.8428733032 6874.0575791855))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7190.7996606335 6851.4331447964 0.0) (10 7175.1598532452 6818.7870326758 0.0) (10 7129.5392901996
6821.0289411244 0.0) (10 7107.8428733032 6843.8914027149 0.0))
((0 . "LWPOLYLINE") (100 . "AcDbEntity") (8 . "PLANTS") (62 . 94) (370 . 13) (100 . "AcDbPolyline") (90 . 3) (70 . 0)
(43 . 0.0) (10 7162.0499010958 6730.7692307692) (10 7138.0090497738 6734.3918552036) (10 7107.8428733032
6734.5397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7185.1435520362 254.5248868778 0.0) (10 7170.8857505346 222.9234137337 0.0) (10 7135.0944634486
232.8189284384 0.0) (10 7111.6141402715 241.3263574661 0.0))
((0 . "LWPOLYLINE") (100 . "AcDbEntity") (8 . "PLANTS") (62 . 94) (370 . 13) (100 . "AcDbPolyline") (90 . 2) (70 . 0)
(43 . 0.0) (10 7111.6141402715 241.3263574661) (10 7115.3846153846 267.7234162896))
((0 . "LWPOLYLINE") (100 . "AcDbEntity") (8 . "PLANTS") (62 . 94) (370 . 13) (100 . "AcDbPolyline") (90 . 3) (70 . 0)
(43 . 0.0) (10 7115.3846153846 6881.5985294118) (10 7130.4673076923 6877.9763574661) (10 7171.9457013575
6877.8280542986))
((0 . "LWPOLYLINE") (100 . "AcDbEntity") (8 . "PLANTS") (62 . 94) (370 . 13) (100 . "AcDbPolyline") (90 . 2) (70 . 0)
(43 . 0.0) (10 7156.8630090498 441.1764705882) (10 7122.9263574661 456.2584841629))
((0 . "LWPOLYLINE") (100 . "AcDbEntity") (8 . "PLANTS") (62 . 94) (370 . 13) (100 . "AcDbPolyline") (90 . 2) (70 . 0)
(43 . 0.0) (10 7134.2385746606 478.882918552) (10 7122.9263574661 456.2584841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7134.2385746606 478.882918552 0.0) (10 7151.8975974798 480.4660518141 0.0) (10 7159.342893078
453.3101840952 0.0) (10 7156.8630090498 441.1764705882 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7149.3212669683 7070.1357466063 0.0) (10 7120.1722151785 7062.5173292335 0.0) (10 7125.9394676938
7089.32865947 0.0) (10 7136.4813535526 7098.8745984591 0.0))
((0 . "LWPOLYLINE") (100 . "AcDbEntity") (8 . "PLANTS") (62 . 94) (370 . 13) (100 . "AcDbPolyline") (90 . 3) (70 . 0)
(43 . 0.0) (10 7194.4587005243 7081.4813943676) (10 7206.9317873303 7013.5746606335) (10 7217.1945701357
6994.7207013575))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7164.403959276 7009.8041855204 0.0) (10 7168.201080875 7033.0048249775 0.0) (10 7134.0951969376
7044.0717521999 0.0) (10 7149.3212669683 7070.1357466063 0.0))
((0 . "LWPOLYLINE") (100 . "AcDbEntity") (8 . "PLANTS") (62 . 94) (370 . 13) (100 . "AcDbPolyline") (90 . 3) (70 . 0)
(43 . 0.0) (10 7149.3212669683 7070.1357466063) (10 7157.0045248869 7080.2436651584) (10 7164.403959276
7081.4479638009))
((0 . "LWPOLYLINE") (100 . "AcDbEntity") (8 . "PLANTS") (62 . 94) (370 . 13) (100 . "AcDbPolyline") (90 . 2) (70 . 0)
(43 . 0.0) (10 7164.403959276 554.2986425339) (10 7156.8630090498 535.4440045249))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7209.6528280543 343.1363122172 0.0) (10 7172.2979823232 361.4462824197 0.0) (10 7185.8033711118
415.2522249814 0.0) (10 7156.8630090498 441.1764705882 0.0))
((0 . "LWPOLYLINE") (100 . "AcDbEntity") (8 . "PLANTS") (62 . 94) (370 . 13) (100 . "AcDbPolyline") (90 . 2) (70 . 0)
(43 . 0.0) (10 7185.1435520362 254.5248868778) (10 7160.6334841629 279.0356334842))
((0 . "LWPOLYLINE") (100 . "AcDbEntity") (8 . "PLANTS") (62 . 94) (370 . 13) (100 . "AcDbPolyline") (90 . 2) (70 . 0)
(43 . 0.0) (10 7160.6334841629 279.0356334842) (10 7171.9457013575 301.6600678733))
((0 . "LWPOLYLINE") (100 . "AcDbEntity") (8 . "PLANTS") (62 . 94) (370 . 13) (100 . "AcDbPolyline") (90 . 2) (70 . 0)
(43 . 0.0) (10 7164.403959276 554.2986425339) (10 7213.4240950226 546.7562217195))
((0 . "LWPOLYLINE") (100 . "AcDbEntity") (8 . "PLANTS") (62 . 94) (370 . 13) (100 . "AcDbPolyline") (90 . 2) (70 . 0)
(43 . 0.0) (10 7168.1752262443 309.1996606335) (10 7171.9457013575 301.6600678733))
((0 . "LWPOLYLINE") (100 . "AcDbEntity") (8 . "PLANTS") (62 . 94) (370 . 13) (100 . "AcDbPolyline") (90 . 2) (70 . 0)
(43 . 0.0) (10 7190.7996606335 6858.9740950226) (10 7171.9457013575 6877.8280542986))
((0 . "LWPOLYLINE") (100 . "AcDbEntity") (8 . "PLANTS") (62 . 94) (370 . 13) (100 . "AcDbPolyline") (90 . 3) (70 . 0)
(43 . 0.0) (10 7183.257918552 6923.0769230769) (10 7182.2015837104 6907.9942307692) (10 7171.9457013575
6877.8280542986))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7185.1435520362 254.5248868778 0.0) (10 7186.1370690864 267.9839043394 0.0) (10 7191.4347999562
295.5715773785 0.0) (10 7171.9457013575 301.6600678733 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7277.0790381802 665.0372953637 0.0) (10 7280.803904342 649.6260418996 0.0) (10 7271.3690250859
632.0414217907 0.0) (10 7281.29739819 618.4021493213 0.0))
((0 . "LWPOLYLINE") (100 . "AcDbEntity") (8 . "PLANTS") (62 . 94) (370 . 13) (100 . "AcDbPolyline") (90 . 3) (70 . 0)
(43 . 0.0) (10 7175.8706997355 778.1524971548) (10 7175.8708144796 776.7731900452) (10 7187.0283936652 761.6883484163))
((0 . "LWPOLYLINE") (100 . "AcDbEntity") (8 . "PLANTS") (62 . 94) (370 . 13) (100 . "AcDbPolyline") (90 . 3) (70 . 0)
(43 . 0.0) (10 7202.1118778281 6960.7840497738) (10 7188.2263574661 6949.4718325792) (10 7183.257918552
6923.0769230769))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7217.1945701358 6934.3891402715 0.0) (10 7213.5172867911 6920.1428384324 0.0) (10 7192.5483046683
6925.1049447544 0.0) (10 7183.257918552 6923.0769230769 0.0))
((0 . "LWPOLYLINE") (100 . "AcDbEntity") (8 . "PLANTS") (62 . 94) (370 . 13) (100 . "AcDbPolyline") (90 . 3) (70 . 0)
(43 . 0.0) (10 7185.1435520362 254.5248868778) (10 7232.2772624434 252.7938914027) (10 7247.3607466063 260.1809954751))
((0 . "LWPOLYLINE") (100 . "AcDbEntity") (8 . "PLANTS") (62 . 94) (370 . 13) (100 . "AcDbPolyline") (90 . 3) (70 . 0)
(43 . 0.0) (10 7190.7996606335 727.7516968326) (10 7184.4558823529 754.1411764706) (10 7187.0283936652 761.6883484163))
((0 . "LWPOLYLINE") (100 . "AcDbEntity") (8 . "PLANTS") (62 . 94) (370 . 13) (100 . "AcDbPolyline") (90 . 2) (70 . 0)
(43 . 0.0) (10 7189.4969241148 762.9231875544) (10 7187.0283936652 761.6883484163))
((0 . "LWPOLYLINE") (100 . "AcDbEntity") (8 . "PLANTS") (62 . 94) (370 . 13) (100 . "AcDbPolyline") (90 . 2) (70 . 0)
(43 . 0.0) (10 7190.7996606335 6851.4331447964) (10 7190.7996606335 6858.9740950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7190.7996606335 6858.9740950226 0.0) (10 7204.9096540396 6893.3204205041 0.0) (10 7242.5060905329
6877.806736358 0.0) (10 7262.443438914 6900.4524886878 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7190.7996606335 6851.4331447964 0.0) (10 7225.7902681291 6825.1210299124 0.0) (10 7295.9660402871
6810.7596888085 0.0) (10 7319.0045248869 6858.9740950226 0.0))
((0 . "LWPOLYLINE") (100 . "AcDbEntity") (8 . "PLANTS") (62 . 94) (370 . 13) (100 . "AcDbPolyline") (90 . 2) (70 . 0)
(43 . 0.0) (10 7190.7996606335 727.7516968326) (10 7194.5701357466 693.8150452489))
((0 . "LWPOLYLINE") (100 . "AcDbEntity") (8 . "PLANTS") (62 . 94) (370 . 13) (100 . "AcDbPolyline") (90 . 2) (70 . 0)
(43 . 0.0) (10 7202.1118778281 735.2941176471) (10 7190.7996606335 727.7516968326))
((0 . "LWPOLYLINE") (100 . "AcDbEntity") (8 . "PLANTS") (62 . 94) (370 . 13) (100 . "AcDbPolyline") (90 . 2) (70 . 0)
(43 . 0.0) (10 7213.4240950226 690.0452488688) (10 7194.5701357466 693.8150452489))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7213.4240950226 580.6928733032 0.0) (10 7187.9145157596 612.185438545 0.0) (10 7204.432343924
659.1716808441 0.0) (10 7194.5701357466 693.8150452489 0.0))
((0 . "LWPOLYLINE") (100 . "AcDbEntity") (8 . "PLANTS") (62 . 94) (370 . 13) (100 . "AcDbPolyline") (90 . 2) (70 . 0)
(43 . 0.0) (10 7202.1118778281 6960.7840497738) (10 7217.1945701357 6934.3891402715))
((0 . "LWPOLYLINE") (100 . "AcDbEntity") (8 . "PLANTS") (62 . 94) (370 . 13) (100 . "AcDbPolyline") (90 . 2) (70 . 0)
(43 . 0.0) (10 7217.1945701357 6987.1797511312) (10 7202.1118778281 6960.7840497738))
((0 . "LWPOLYLINE") (100 . "AcDbEntity") (8 . "PLANTS") (62 . 94) (370 . 13) (100 . "AcDbPolyline") (90 . 2) (70 . 0)
(43 . 0.0) (10 7209.6528280543 343.1363122172) (10 7228.5067873303 343.1363122172))
((0 . "LWPOLYLINE") (100 . "AcDbEntity") (8 . "PLANTS") (62 . 94) (370 . 13) (100 . "AcDbPolyline") (90 . 3) (70 . 0)
(43 . 0.0) (10 7209.6528280543 343.1363122172) (10 7210.8570135747 298.0358597285) (10 7247.3607466063 267.7234162896))
((0 . "LWPOLYLINE") (100 . "AcDbEntity") (8 . "PLANTS") (62 . 94) (370 . 13) (100 . "AcDbPolyline") (90 . 2) (70 . 0)
(43 . 0.0) (10 7213.4240950226 580.6928733032) (10 7213.4240950226 546.7562217195))
((0 . "LWPOLYLINE") (100 . "AcDbEntity") (8 . "PLANTS") (62 . 94) (370 . 13) (100 . "AcDbPolyline") (90 . 3) (70 . 0)
(43 . 0.0) (10 7213.4240950226 580.6928733032) (10 7227.30260181 595.7777149321) (10 7232.2772624434 629.7143665158))
((0 . "LWPOLYLINE") (100 . "AcDbEntity") (8 . "PLANTS") (62 . 94) (370 . 13) (100 . "AcDbPolyline") (90 . 2) (70 . 0)
(43 . 0.0) (10 7224.7363122172 501.5073529412) (10 7213.4240950226 546.7562217195))
((0 . "LWPOLYLINE") (100 . "AcDbEntity") (8 . "PLANTS") (62 . 94) (370 . 13) (100 . "AcDbPolyline") (90 . 2) (70 . 0)
(43 . 0.0) (10 7217.1945701357 6987.1797511312) (10 7217.1945701357 6994.7207013575))
((0 . "LWPOLYLINE") (100 . "AcDbEntity") (8 . "PLANTS") (62 . 94) (370 . 13) (100 . "AcDbPolyline") (90 . 2) (70 . 0)
(43 . 0.0) (10 7243.589479638 7013.5746606335) (10 7217.1945701357 6994.7207013575))
((0 . "LWPOLYLINE") (100 . "AcDbEntity") (8 . "PLANTS") (62 . 94) (370 . 13) (100 . "AcDbPolyline") (90 . 3) (70 . 0)
(43 . 0.0) (10 7217.1945701357 6987.1797511312) (10 7239.8190045249 6979.7863122172) (10 7258.6729638009
6979.6380090498))
((0 . "LWPOLYLINE") (100 . "AcDbEntity") (8 . "PLANTS") (62 . 94) (370 . 13) (100 . "AcDbPolyline") (90 . 2) (70 . 0)
(43 . 0.0) (10 7217.1945701357 6934.3891402715) (10 7251.1312217195 6934.3891402715))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4528516956) (40
. 1) (40 . 1) (40 . 1) (40 . 1) (10 7224.7363122172 501.5073529412 0.0) (10 7221.222863194 477.8772204828 0.0) (10
7222.1121796536 424.8296617675 0.0) (10 7235.5570345678 372.7329909057 0.0) (10 7228.5067873303 343.1363122172 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7224.7363122172 501.5073529412 0.0) (10 7250.4380142004 500.1277682866 0.0) (10 7257.1110201199
530.9902313485 0.0) (10 7281.29739819 531.6742081448 0.0))
((0 . "LWPOLYLINE") (100 . "AcDbEntity") (8 . "PLANTS") (62 . 94) (370 . 13) (100 . "AcDbPolyline") (90 . 2) (70 . 0)
(43 . 0.0) (10 7228.5067873303 343.1363122172) (10 7243.589479638 328.0542986425))
((0 . "LWPOLYLINE") (100 . "AcDbEntity") (8 . "PLANTS") (62 . 94) (370 . 13) (100 . "AcDbPolyline") (90 . 2) (70 . 0)
(43 . 0.0) (10 7243.589479638 7013.5746606335) (10 7262.443438914 7013.5746606335))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7273.7556561086 7066.3652714932 0.0) (10 7245.4983763372 7076.8518295709 0.0) (10 7229.1410453325
7032.9591458472 0.0) (10 7243.589479638 7013.5746606335 0.0))
((0 . "LWPOLYLINE") (100 . "AcDbEntity") (8 . "PLANTS") (62 . 94) (370 . 13) (100 . "AcDbPolyline") (90 . 3) (70 . 0)
(43 . 0.0) (10 7243.589479638 328.0542986425) (10 7250.9828054299 282.8054298643) (10 7247.3607466063 267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7281.29739819 403.4700226244 0.0) (10 7250.0836431221 387.0356465992 0.0) (10 7269.6392952852
345.4808831336 0.0) (10 7243.589479638 328.0542986425 0.0))
((0 . "LWPOLYLINE") (100 . "AcDbEntity") (8 . "PLANTS") (62 . 94) (370 . 13) (100 . "AcDbPolyline") (90 . 2) (70 . 0)
(43 . 0.0) (10 7247.3607466063 260.1809954751) (10 7247.3607466063 267.7234162896))
((0 . "LWPOLYLINE") (100 . "AcDbEntity") (8 . "PLANTS") (62 . 94) (370 . 13) (100 . "AcDbPolyline") (90 . 2) (70 . 0)
(43 . 0.0) (10 7247.3607466063 260.1809954751) (10 7277.5261312217 256.411199095))
((0 . "LWPOLYLINE") (100 . "AcDbEntity") (8 . "PLANTS") (62 . 94) (370 . 13) (100 . "AcDbPolyline") (90 . 2) (70 . 0)
(43 . 0.0) (10 7251.1312217195 6934.3891402715) (10 7262.443438914 6900.4524886878))
((0 . "LWPOLYLINE") (100 . "AcDbEntity") (8 . "PLANTS") (62 . 94) (370 . 13) (100 . "AcDbPolyline") (90 . 2) (70 . 0)
(43 . 0.0) (10 7251.1312217195 6934.3891402715) (10 7262.443438914 6968.3257918552))
((0 . "LWPOLYLINE") (100 . "AcDbEntity") (8 . "PLANTS") (62 . 94) (370 . 13) (100 . "AcDbPolyline") (90 . 2) (70 . 0)
(43 . 0.0) (10 7258.6729638009 6979.6380090498) (10 7262.443438914 6968.3257918552))
((0 . "LWPOLYLINE") (100 . "AcDbEntity") (8 . "PLANTS") (62 . 94) (370 . 13) (100 . "AcDbPolyline") (90 . 3) (70 . 0)
(43 . 0.0) (10 7258.6729638009 6979.6380090498) (10 7262.2957013575 6987.1863122172) (10 7262.443438914
7013.5746606335))
((0 . "LWPOLYLINE") (100 . "AcDbEntity") (8 . "PLANTS") (62 . 94) (370 . 13) (100 . "AcDbPolyline") (90 . 3) (70 . 0)
(43 . 0.0) (10 7285.0678733032 7047.5113122172) (10 7280.2409502262 7025.0351809955) (10 7262.443438914
7013.5746606335))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7337.8584841629 7006.032918552 0.0) (10 7297.6694716551 7018.4129153231 0.0) (10 7300.1445167482
6962.3663721136 0.0) (10 7262.443438914 6968.3257918552 0.0))
((0 . "LWPOLYLINE") (100 . "AcDbEntity") (8 . "PLANTS") (62 . 94) (370 . 13) (100 . "AcDbPolyline") (90 . 3) (70 . 0)
(43 . 0.0) (10 7296.3800904977 6892.9107466063) (10 7277.5261312217 6900.3041855204) (10 7262.443438914
6900.4524886878))
((0 . "LWPOLYLINE") (100 . "AcDbEntity") (8 . "PLANTS") (62 . 94) (370 . 13) (100 . "AcDbPolyline") (90 . 2) (70 . 0)
(43 . 0.0) (10 7273.7556561086 7066.3652714932) (10 7285.0678733032 7047.5113122172))
((0 . "LWPOLYLINE") (100 . "AcDbEntity") (8 . "PLANTS") (62 . 94) (370 . 13) (100 . "AcDbPolyline") (90 . 3) (70 . 0)
(43 . 0.0) (10 7273.7556561086 7066.3652714932) (10 7277.5199095023 7081.4479638009) (10 7277.5202684995
7107.9920062818))
((0 . "LWPOLYLINE") (100 . "AcDbEntity") (8 . "PLANTS") (62 . 94) (370 . 13) (100 . "AcDbPolyline") (90 . 2) (70 . 0)
(43 . 0.0) (10 7345.3994343891 882.3529411765) (10 7338.7740785521 881.6746593304))
((0 . "LWPOLYLINE") (100 . "AcDbEntity") (8 . "PLANTS") (62 . 94) (370 . 13) (100 . "AcDbPolyline") (90 . 3) (70 . 0)
(43 . 0.0) (10 7330.3167420814 241.3263574661) (10 7288.8383484163 242.5312217195) (10 7277.5261312217 256.411199095))
((0 . "LWPOLYLINE") (100 . "AcDbEntity") (8 . "PLANTS") (62 . 94) (370 . 13) (100 . "AcDbPolyline") (90 . 3) (70 . 0)
(43 . 0.0) (10 7311.4627828054 279.0356334842) (10 7296.3800904977 274.0596153846) (10 7277.5261312217 256.411199095))
((0 . "LWPOLYLINE") (100 . "AcDbEntity") (8 . "PLANTS") (62 . 94) (370 . 13) (100 . "AcDbPolyline") (90 . 3) (70 . 0)
(43 . 0.0) (10 7281.29739819 531.6742081448) (10 7286.2720588235 493.967760181) (10 7300.1505656109 482.6555429864))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7303.9218325792 576.9230769231 0.0) (10 7285.025895836 570.572211945 0.0) (10 7297.1197683304
542.185160506 0.0) (10 7281.29739819 531.6742081448 0.0))
((0 . "LWPOLYLINE") (100 . "AcDbEntity") (8 . "PLANTS") (62 . 94) (370 . 13) (100 . "AcDbPolyline") (90 . 3) (70 . 0)
(43 . 0.0) (10 7300.1505656109 467.5707013575) (10 7293.6590497738 456.2584841629) (10 7281.29739819 403.4700226244))
((0 . "LWPOLYLINE") (100 . "AcDbEntity") (8 . "PLANTS") (62 . 94) (370 . 13) (100 . "AcDbPolyline") (90 . 3) (70 . 0)
(43 . 0.0) (10 7281.29739819 403.4700226244) (10 7322.775 407.0851809955) (10 7334.0872171946 399.69739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7285.0678733032 7047.5113122172 0.0) (10 7308.7342817931 7053.6689399954 0.0) (10 7299.1598083559
7100.435022388 0.0) (10 7337.8584841629 7077.6774886878 0.0))
((0 . "LWPOLYLINE") (100 . "AcDbEntity") (8 . "PLANTS") (62 . 94) (370 . 13) (100 . "AcDbPolyline") (90 . 2) (70 . 0)
(43 . 0.0) (10 7324.9562295599 823.6396935632) (10 7352.9411764706 825.7918552036))
((0 . "LWPOLYLINE") (100 . "AcDbEntity") (8 . "PLANTS") (62 . 94) (370 . 13) (100 . "AcDbPolyline") (90 . 2) (70 . 0)
(43 . 0.0) (10 7296.3800904977 6892.9107466063) (10 7319.0045248869 6885.3697963801))
((0 . "LWPOLYLINE") (100 . "AcDbEntity") (8 . "PLANTS") (62 . 94) (370 . 13) (100 . "AcDbPolyline") (90 . 2) (70 . 0)
(43 . 0.0) (10 7296.3800904977 6892.9107466063) (10 7300.1505656109 6919.3064479638))
((0 . "LWPOLYLINE") (100 . "AcDbEntity") (8 . "PLANTS") (62 . 94) (370 . 13) (100 . "AcDbPolyline") (90 . 2) (70 . 0)
(43 . 0.0) (10 7300.1505656109 467.5707013575) (10 7300.1505656109 482.6555429864))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7341.6289592761 599.5475113122 0.0) (10 7338.2221273365 558.9223365594 0.0) (10 7326.2787942818
514.4532235456 0.0) (10 7300.1505656109 482.6555429864 0.0))
((0 . "LWPOLYLINE") (100 . "AcDbEntity") (8 . "PLANTS") (62 . 94) (370 . 13) (100 . "AcDbPolyline") (90 . 3) (70 . 0)
(43 . 0.0) (10 7360.482918552 493.967760181) (10 7322.775 472.392081448) (10 7300.1505656109 467.5707013575))
((0 . "LWPOLYLINE") (100 . "AcDbEntity") (8 . "PLANTS") (62 . 94) (370 . 13) (100 . "AcDbPolyline") (90 . 2) (70 . 0)
(43 . 0.0) (10 7311.4627828054 339.3665158371) (10 7303.9218325792 335.596719457))
((0 . "LWPOLYLINE") (100 . "AcDbEntity") (8 . "PLANTS") (62 . 94) (370 . 13) (100 . "AcDbPolyline") (90 . 2) (70 . 0)
(43 . 0.0) (10 7334.0872171946 6941.9308823529) (10 7311.4627828054 6938.1596153846))
((0 . "LWPOLYLINE") (100 . "AcDbEntity") (8 . "PLANTS") (62 . 94) (370 . 13) (100 . "AcDbPolyline") (90 . 2) (70 . 0)
(43 . 0.0) (10 7311.4627828054 339.3665158371) (10 7315.2340497738 320.5118778281))
((0 . "LWPOLYLINE") (100 . "AcDbEntity") (8 . "PLANTS") (62 . 94) (370 . 13) (100 . "AcDbPolyline") (90 . 2) (70 . 0)
(43 . 0.0) (10 7311.4627828054 339.3665158371) (10 7334.0872171946 399.69739819))
((0 . "LWPOLYLINE") (100 . "AcDbEntity") (8 . "PLANTS") (62 . 94) (370 . 13) (100 . "AcDbPolyline") (90 . 2) (70 . 0)
(43 . 0.0) (10 7311.4627828054 279.0356334842) (10 7330.3167420814 267.7234162896))
((0 . "LWPOLYLINE") (100 . "AcDbEntity") (8 . "PLANTS") (62 . 94) (370 . 13) (100 . "AcDbPolyline") (90 . 2) (70 . 0)
(43 . 0.0) (10 7311.4627828054 279.0356334842) (10 7315.2340497738 320.5118778281))
((0 . "LWPOLYLINE") (100 . "AcDbEntity") (8 . "PLANTS") (62 . 94) (370 . 13) (100 . "AcDbPolyline") (90 . 3) (70 . 0)
(43 . 0.0) (10 7371.7951357466 361.9909502262) (10 7337.8515837104 325.340158371) (10 7315.2340497738 320.5118778281))
((0 . "LWPOLYLINE") (100 . "AcDbEntity") (8 . "PLANTS") (62 . 94) (370 . 13) (100 . "AcDbPolyline") (90 . 2) (70 . 0)
(43 . 0.0) (10 7319.0045248869 6885.3697963801) (10 7319.0045248869 6858.9740950226))
((0 . "LWPOLYLINE") (100 . "AcDbEntity") (8 . "PLANTS") (62 . 94) (370 . 13) (100 . "AcDbPolyline") (90 . 2) (70 . 0)
(43 . 0.0) (10 7337.8584841629 6904.2229638009) (10 7319.0045248869 6885.3697963801))
((0 . "LWPOLYLINE") (100 . "AcDbEntity") (8 . "PLANTS") (62 . 94) (370 . 13) (100 . "AcDbPolyline") (90 . 3) (70 . 0)
(43 . 0.0) (10 7386.8778280543 6855.2036199095) (10 7334.0872171946 6851.5809954751) (10 7319.0045248869
6858.9740950226))
((0 . "LWPOLYLINE") (100 . "AcDbEntity") (8 . "PLANTS") (62 . 94) (370 . 13) (100 . "AcDbPolyline") (90 . 2) (70 . 0)
(43 . 0.0) (10 7330.3167420814 241.3263574661) (10 7330.3167420814 267.7234162896))
((0 . "LWPOLYLINE") (100 . "AcDbEntity") (8 . "PLANTS") (62 . 94) (370 . 13) (100 . "AcDbPolyline") (90 . 3) (70 . 0)
(43 . 0.0) (10 7386.8778280543 312.9722850679) (10 7371.9428733032 308.1440045249) (10 7330.3167420814 267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7330.3167420815 241.326357466 0.0) (10 7356.3878967525 224.6101398521 0.0) (10 7396.5117774682
227.4117149005 0.0) (10 7420.814479638 245.0989819004 0.0))
((0 . "LWPOLYLINE") (100 . "AcDbEntity") (8 . "PLANTS") (62 . 94) (370 . 13) (100 . "AcDbPolyline") (90 . 2) (70 . 0)
(43 . 0.0) (10 7334.0872171946 6941.9308823529) (10 7337.8584841629 6904.2229638009))
((0 . "LWPOLYLINE") (100 . "AcDbEntity") (8 . "PLANTS") (62 . 94) (370 . 13) (100 . "AcDbPolyline") (90 . 3) (70 . 0)
(43 . 0.0) (10 7334.0872171946 6941.9308823529) (10 7340.4309954751 6979.6380090498) (10 7337.8584841629
7006.032918552))
((0 . "LWPOLYLINE") (100 . "AcDbEntity") (8 . "PLANTS") (62 . 94) (370 . 13) (100 . "AcDbPolyline") (90 . 2) (70 . 0)
(43 . 0.0) (10 7341.628959276 599.5475113122) (10 7334.0872171946 610.8597285068))
((0 . "LWPOLYLINE") (100 . "AcDbEntity") (8 . "PLANTS") (62 . 94) (370 . 13) (100 . "AcDbPolyline") (90 . 2) (70 . 0)
(43 . 0.0) (10 7334.0872171946 399.69739819) (10 7349.1707013575 399.69739819))
((0 . "LWPOLYLINE") (100 . "AcDbEntity") (8 . "PLANTS") (62 . 94) (370 . 13) (100 . "AcDbPolyline") (90 . 2) (70 . 0)
(43 . 0.0) (10 7337.6186772908 7127.223497095) (10 7337.8584841629 7096.5306561086))
((0 . "LWPOLYLINE") (100 . "AcDbEntity") (8 . "PLANTS") (62 . 94) (370 . 13) (100 . "AcDbPolyline") (90 . 2) (70 . 0)
(43 . 0.0) (10 7337.8584841629 7096.5306561086) (10 7337.8584841629 7077.6774886878))
((0 . "LWPOLYLINE") (100 . "AcDbEntity") (8 . "PLANTS") (62 . 94) (370 . 13) (100 . "AcDbPolyline") (90 . 3) (70 . 0)
(43 . 0.0) (10 7409.5022624434 7138.0090497738) (10 7368.0238687783 7101.5062217195) (10 7337.8584841629
7096.5306561086))
((0 . "LWPOLYLINE") (100 . "AcDbEntity") (8 . "PLANTS") (62 . 94) (370 . 13) (100 . "AcDbPolyline") (90 . 2) (70 . 0)
(43 . 0.0) (10 7337.8584841629 7006.032918552) (10 7337.8584841629 7077.6774886878))
((0 . "LWPOLYLINE") (100 . "AcDbEntity") (8 . "PLANTS") (62 . 94) (370 . 13) (100 . "AcDbPolyline") (90 . 2) (70 . 0)
(43 . 0.0) (10 7337.8584841629 7006.032918552) (10 7352.9411764706 7006.032918552))
((0 . "LWPOLYLINE") (100 . "AcDbEntity") (8 . "PLANTS") (62 . 94) (370 . 13) (100 . "AcDbPolyline") (90 . 2) (70 . 0)
(43 . 0.0) (10 7337.8584841629 6904.2229638009) (10 7368.0238687783 6904.2229638009))
((0 . "LWPOLYLINE") (100 . "AcDbEntity") (8 . "PLANTS") (62 . 94) (370 . 13) (100 . "AcDbPolyline") (90 . 3) (70 . 0)
(43 . 0.0) (10 7341.628959276 599.5475113122) (10 7351.7369909502 607.0947963801) (10 7352.9411764706 622.1719457014))
((0 . "LWPOLYLINE") (100 . "AcDbEntity") (8 . "PLANTS") (62 . 94) (370 . 13) (100 . "AcDbPolyline") (90 . 2) (70 . 0)
(43 . 0.0) (10 7345.3994343891 885.4957956259) (10 7345.3994343891 882.3529411765))
((0 . "LWPOLYLINE") (100 . "AcDbEntity") (8 . "PLANTS") (62 . 94) (370 . 13) (100 . "AcDbPolyline") (90 . 2) (70 . 0)
(43 . 0.0) (10 7345.3994343891 882.3529411765) (10 7347.1136407158 881.7816819181))
((0 . "LWPOLYLINE") (100 . "AcDbEntity") (8 . "PLANTS") (62 . 94) (370 . 13) (100 . "AcDbPolyline") (90 . 3) (70 . 0)
(43 . 0.0) (10 7371.7951357466 361.9909502262) (10 7363.0554298643 384.6153846154) (10 7349.1707013575 399.69739819))
((0 . "LWPOLYLINE") (100 . "AcDbEntity") (8 . "PLANTS") (62 . 94) (370 . 13) (100 . "AcDbPolyline") (90 . 3) (70 . 0)
(43 . 0.0) (10 7356.7116515837 426.0944570136) (10 7350.2270361991 414.782239819) (10 7349.1707013575 399.69739819))
((0 . "LWPOLYLINE") (100 . "AcDbEntity") (8 . "PLANTS") (62 . 94) (370 . 13) (100 . "AcDbPolyline") (90 . 2) (70 . 0)
(43 . 0.0) (10 7379.3360859729 6979.6380090498) (10 7352.9411764706 7006.032918552))
((0 . "LWPOLYLINE") (100 . "AcDbEntity") (8 . "PLANTS") (62 . 94) (370 . 13) (100 . "AcDbPolyline") (90 . 3) (70 . 0)
(43 . 0.0) (10 7368.0238687783 7039.9695701357) (10 7366.8197963801 7024.8868778281) (10 7352.9411764706
7006.032918552))
((0 . "LWPOLYLINE") (100 . "AcDbEntity") (8 . "PLANTS") (62 . 94) (370 . 13) (100 . "AcDbPolyline") (90 . 2) (70 . 0)
(43 . 0.0) (10 7352.9411764706 825.7918552036) (10 7374.6224743998 822.1792089362))
((0 . "LWPOLYLINE") (100 . "AcDbEntity") (8 . "PLANTS") (62 . 94) (370 . 13) (100 . "AcDbPolyline") (90 . 2) (70 . 0)
(43 . 0.0) (10 7352.9411764706 825.7918552036) (10 7355.6232507013 863.3441936162))
((0 . "LWPOLYLINE") (100 . "AcDbEntity") (8 . "PLANTS") (62 . 94) (370 . 13) (100 . "AcDbPolyline") (90 . 3) (70 . 0)
(43 . 0.0) (10 7352.9411764706 622.1719457014) (10 7350.3816742081 633.4779411765) (10 7360.482918552 641.0265837104))
((0 . "LWPOLYLINE") (100 . "AcDbEntity") (8 . "PLANTS") (62 . 94) (370 . 13) (100 . "AcDbPolyline") (90 . 3) (70 . 0)
(43 . 0.0) (10 7352.9411764706 622.1719457014) (10 7363.0423076923 629.7192307692) (10 7360.482918552 641.0265837104))
((0 . "LWPOLYLINE") (100 . "AcDbEntity") (8 . "PLANTS") (62 . 94) (370 . 13) (100 . "AcDbPolyline") (90 . 3) (70 . 0)
(43 . 0.0) (10 7360.482918552 493.967760181) (10 7367.8692307692 478.882918552) (10 7356.7116515837 426.0944570136))
((0 . "LWPOLYLINE") (100 . "AcDbEntity") (8 . "PLANTS") (62 . 94) (370 . 13) (100 . "AcDbPolyline") (90 . 2) (70 . 0)
(43 . 0.0) (10 7356.7116515837 426.0944570136) (10 7394.4195701357 429.8642533937))
((0 . "LWPOLYLINE") (100 . "AcDbEntity") (8 . "PLANTS") (62 . 94) (370 . 13) (100 . "AcDbPolyline") (90 . 3) (70 . 0)
(43 . 0.0) (10 7371.7951357466 656.1085972851) (10 7365.3028280543 652.1834841629) (10 7360.482918552 641.0265837104))
((0 . "LWPOLYLINE") (100 . "AcDbEntity") (8 . "PLANTS") (62 . 94) (370 . 13) (100 . "AcDbPolyline") (90 . 3) (70 . 0)
(43 . 0.0) (10 7360.482918552 493.967760181) (10 7368.17239819 504.2297511312) (10 7401.960520362 522.2483031674))
((0 . "LWPOLYLINE") (100 . "AcDbEntity") (8 . "PLANTS") (62 . 94) (370 . 13) (100 . "AcDbPolyline") (90 . 2) (70 . 0)
(43 . 0.0) (10 7368.0238687783 6915.5351809955) (10 7368.0238687783 6904.2229638009))
((0 . "LWPOLYLINE") (100 . "AcDbEntity") (8 . "PLANTS") (62 . 94) (370 . 13) (100 . "AcDbPolyline") (90 . 3) (70 . 0)
(43 . 0.0) (10 7368.0238687783 6915.5351809955) (10 7368.1716063348 6949.4718325792) (10 7379.3360859729
6972.0962669683))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7443.4389140272 6896.6820135747 0.0) (10 7438.4535371356 6934.1211608347 0.0) (10 7394.0035335188
6922.0755295805 0.0) (10 7368.0238687783 6915.5351809955 0.0))
((0 . "LWPOLYLINE") (100 . "AcDbEntity") (8 . "PLANTS") (62 . 94) (370 . 13) (100 . "AcDbPolyline") (90 . 3) (70 . 0)
(43 . 0.0) (10 7368.0238687783 6904.2229638009) (10 7372.8445701357 6885.3697963801) (10 7386.8778280543
6862.745361991))
((0 . "LWPOLYLINE") (100 . "AcDbEntity") (8 . "PLANTS") (62 . 94) (370 . 13) (100 . "AcDbPolyline") (90 . 2) (70 . 0)
(43 . 0.0) (10 7371.7951357466 656.1085972851) (10 7379.3360859729 656.1085972851))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7371.7951357466 656.1085972851 0.0) (10 7368.6463947752 690.2111290275 0.0) (10 7388.022156387
722.1959521032 0.0) (10 7409.2123604468 747.2344558344 0.0))
((0 . "LWPOLYLINE") (100 . "AcDbEntity") (8 . "PLANTS") (62 . 94) (370 . 13) (100 . "AcDbPolyline") (90 . 2) (70 . 0)
(43 . 0.0) (10 7390.6483031674 358.2211538462) (10 7371.7951357466 361.9909502262))
((0 . "LWPOLYLINE") (100 . "AcDbEntity") (8 . "PLANTS") (62 . 94) (370 . 13) (100 . "AcDbPolyline") (90 . 2) (70 . 0)
(43 . 0.0) (10 7379.3360859729 7073.9062217195) (10 7379.3360859729 7066.3652714932))
((0 . "LWPOLYLINE") (100 . "AcDbEntity") (8 . "PLANTS") (62 . 94) (370 . 13) (100 . "AcDbPolyline") (90 . 2) (70 . 0)
(43 . 0.0) (10 7379.3360859729 6979.6380090498) (10 7379.3360859729 6972.0962669683))
((0 . "LWPOLYLINE") (100 . "AcDbEntity") (8 . "PLANTS") (62 . 94) (370 . 13) (100 . "AcDbPolyline") (90 . 2) (70 . 0)
(43 . 0.0) (10 7379.3360859729 6979.6380090498) (10 7409.5022624434 7013.5746606335))
((0 . "LWPOLYLINE") (100 . "AcDbEntity") (8 . "PLANTS") (62 . 94) (370 . 13) (100 . "AcDbPolyline") (90 . 3) (70 . 0)
(43 . 0.0) (10 7443.4389140271 6945.7013574661) (10 7409.5022624434 6963.5054298643) (10 7379.3360859729
6972.0962669683))
((0 . "LWPOLYLINE") (100 . "AcDbEntity") (8 . "PLANTS") (62 . 94) (370 . 13) (100 . "AcDbPolyline") (90 . 2) (70 . 0)
(43 . 0.0) (10 7386.8778280543 6855.2036199095) (10 7386.8778280543 6862.745361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7443.4389140272 6896.6820135747 0.0) (10 7434.5385914204 6870.9199124241 0.0) (10 7401.9974316596
6881.7301988188 0.0) (10 7386.8778280543 6862.745361991 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7386.8778280543 6855.2036199095 0.0) (10 7414.0106847776 6827.9314957885 0.0) (10 7457.6007428439
6832.2479135098 0.0) (10 7492.4582579185 6840.1209276018 0.0))
((0 . "LWPOLYLINE") (100 . "AcDbEntity") (8 . "PLANTS") (62 . 94) (370 . 13) (100 . "AcDbPolyline") (90 . 2) (70 . 0)
(43 . 0.0) (10 7386.8778280543 312.9722850679) (10 7420.814479638 245.0989819005))
((0 . "LWPOLYLINE") (100 . "AcDbEntity") (8 . "PLANTS") (62 . 94) (370 . 13) (100 . "AcDbPolyline") (90 . 3) (70 . 0)
(43 . 0.0) (10 7386.8778280543 312.9722850679) (10 7391.6978506787 324.1291855204) (10 7398.1900452489 328.0542986425))
((0 . "LWPOLYLINE") (100 . "AcDbEntity") (8 . "PLANTS") (62 . 94) (370 . 13) (100 . "AcDbPolyline") (90 . 2) (70 . 0)
(43 . 0.0) (10 7390.6483031674 358.2211538462) (10 7398.1900452489 328.0542986425))
((0 . "LWPOLYLINE") (100 . "AcDbEntity") (8 . "PLANTS") (62 . 94) (370 . 13) (100 . "AcDbPolyline") (90 . 2) (70 . 0)
(43 . 0.0) (10 7390.6483031674 358.2211538462) (10 7394.4195701357 392.1578054299))
((0 . "LWPOLYLINE") (100 . "AcDbEntity") (8 . "PLANTS") (62 . 94) (370 . 13) (100 . "AcDbPolyline") (90 . 3) (70 . 0)
(43 . 0.0) (10 7420.814479638 403.4700226244) (10 7405.7380090498 407.3944570136) (10 7394.4195701357 429.8642533937))
((0 . "LWPOLYLINE") (100 . "AcDbEntity") (8 . "PLANTS") (62 . 94) (370 . 13) (100 . "AcDbPolyline") (90 . 3) (70 . 0)
(43 . 0.0) (10 7394.4195701357 429.8642533937) (10 7405.8795248869 448.7188914027) (10 7481.146040724 524.1317873303))
((0 . "LWPOLYLINE") (100 . "AcDbEntity") (8 . "PLANTS") (62 . 94) (370 . 13) (100 . "AcDbPolyline") (90 . 3) (70 . 0)
(43 . 0.0) (10 7398.1900452489 328.0542986425) (10 7424.4372171946 315.6926470588) (10 7458.5216063348 275.2630090498))
((0 . "LWPOLYLINE") (100 . "AcDbEntity") (8 . "PLANTS") (62 . 94) (370 . 13) (100 . "AcDbPolyline") (90 . 2) (70 . 0)
(43 . 0.0) (10 7401.960520362 522.2483031674) (10 7413.2727375566 501.5073529412))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7401.9605203619 522.2483031674 0.0) (10 7388.2534656406 572.9954794615 0.0) (10 7457.2724550112
609.8691087792 0.0) (10 7447.513111693 664.2494948008 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6635421087) (40
. 1) (40 . 1) (40 . 1) (40 . 1) (10 7401.960520362 522.2483031674 0.0) (10 7443.5975894313 545.4589001953 0.0) (10
7494.4022394025 599.2919865742 0.0) (10 7561.9228205479 630.889978718 0.0) (10 7586.7279411765 629.7143665159 0.0))
((0 . "LWPOLYLINE") (100 . "AcDbEntity") (8 . "PLANTS") (62 . 94) (370 . 13) (100 . "AcDbPolyline") (90 . 2) (70 . 0)
(43 . 0.0) (10 7409.5022624434 7013.5746606335) (10 7420.814479638 7009.8041855204))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7469.8338235294 7111.6141402715 0.0) (10 7438.3763666204 7089.58697204 0.0) (10 7414.2001390333
7051.2791137981 0.0) (10 7409.5022624434 7013.5746606335 0.0))
((0 . "LWPOLYLINE") (100 . "AcDbEntity") (8 . "PLANTS") (62 . 94) (370 . 13) (100 . "AcDbPolyline") (90 . 3) (70 . 0)
(43 . 0.0) (10 7420.814479638 403.4700226244) (10 7428.5108597285 384.7631221719) (10 7450.9806561086 373.3031674208))
((0 . "LWPOLYLINE") (100 . "AcDbEntity") (8 . "PLANTS") (62 . 94) (370 . 13) (100 . "AcDbPolyline") (90 . 2) (70 . 0)
(43 . 0.0) (10 7420.814479638 403.4700226244) (10 7443.4389140271 414.782239819))
((0 . "LWPOLYLINE") (100 . "AcDbEntity") (8 . "PLANTS") (62 . 94) (370 . 13) (100 . "AcDbPolyline") (90 . 3) (70 . 0)
(43 . 0.0) (10 7462.2928733032 260.1809954751) (10 7447.2093891403 246.3023755656) (10 7420.814479638 245.0989819005))
((0 . "LWPOLYLINE") (100 . "AcDbEntity") (8 . "PLANTS") (62 . 94) (370 . 13) (100 . "AcDbPolyline") (90 . 3) (70 . 0)
(43 . 0.0) (10 7439.668438914 7006.032918552) (10 7443.4389140271 7002.2624434389) (10 7454.7511312217 7002.2624434389))
((0 . "LWPOLYLINE") (100 . "AcDbEntity") (8 . "PLANTS") (62 . 94) (370 . 13) (100 . "AcDbPolyline") (90 . 2) (70 . 0)
(43 . 0.0) (10 7488.6877828054 6896.6820135747) (10 7443.4389140271 6896.6820135747))
((0 . "LWPOLYLINE") (100 . "AcDbEntity") (8 . "PLANTS") (62 . 94) (370 . 13) (100 . "AcDbPolyline") (90 . 3) (70 . 0)
(43 . 0.0) (10 7443.4389140271 414.782239819) (10 7450.832918552 392.1578054299) (10 7450.9806561086 373.3031674208))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7522.6244343891 490.1951357466 0.0) (10 7487.6112924098 477.6398193603 0.0) (10 7456.5209643599
450.0110514455 0.0) (10 7443.4389140271 414.782239819 0.0))
((0 . "LWPOLYLINE") (100 . "AcDbEntity") (8 . "PLANTS") (62 . 94) (370 . 13) (100 . "AcDbPolyline") (90 . 3) (70 . 0)
(43 . 0.0) (10 7458.5216063348 358.2211538462) (10 7450.9806561086 365.7607466063) (10 7450.9806561086 373.3031674208))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7454.7511312217 7002.2624434389 0.0) (10 7455.3453612183 6968.556058456 0.0) (10 7495.807884053
6956.1356129456 0.0) (10 7500 6923.0769230769 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7545.2488687782 6972.0962669683 0.0) (10 7514.8156400645 6971.7096603364 0.0) (10 7488.0390205624
7031.6450664014 0.0) (10 7454.7511312216 7002.2624434389 0.0))
((0 . "LWPOLYLINE") (100 . "AcDbEntity") (8 . "PLANTS") (62 . 94) (370 . 13) (100 . "AcDbPolyline") (90 . 3) (70 . 0)
(43 . 0.0) (10 7458.5216063348 358.2211538462) (10 7463.3492081448 328.0542986425) (10 7473.6050904977 309.1996606335))
((0 . "LWPOLYLINE") (100 . "AcDbEntity") (8 . "PLANTS") (62 . 94) (370 . 13) (100 . "AcDbPolyline") (90 . 3) (70 . 0)
(43 . 0.0) (10 7511.3122171946 392.1578054299) (10 7484.9173076923 370.5890271493) (10 7458.5216063348 358.2211538462))
((0 . "LWPOLYLINE") (100 . "AcDbEntity") (8 . "PLANTS") (62 . 94) (370 . 13) (100 . "AcDbPolyline") (90 . 3) (70 . 0)
(43 . 0.0) (10 7462.2928733032 260.1809954751) (10 7458.5216063348 263.9507918552) (10 7458.5216063348 275.2630090498))
((0 . "LWPOLYLINE") (100 . "AcDbEntity") (8 . "PLANTS") (62 . 94) (370 . 13) (100 . "AcDbPolyline") (90 . 3) (70 . 0)
(43 . 0.0) (10 7458.5216063348 275.2630090498) (10 7472.4009049774 290.3478506787) (10 7473.6050904977 309.1996606335))
((0 . "LWPOLYLINE") (100 . "AcDbEntity") (8 . "PLANTS") (62 . 94) (370 . 13) (100 . "AcDbPolyline") (90 . 2) (70 . 0)
(43 . 0.0) (10 7462.2928733032 260.1809954751) (10 7481.146040724 260.1809954751))
((0 . "LWPOLYLINE") (100 . "AcDbEntity") (8 . "PLANTS") (62 . 94) (370 . 13) (100 . "AcDbPolyline") (90 . 2) (70 . 0)
(43 . 0.0) (10 7500 309.1996606335) (10 7473.6050904977 309.1996606335))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7481.146040724 260.1809954751 0.0) (10 7496.4061940024 225.5328573244 0.0) (10 7555.2083128929
212.7538243826 0.0) (10 7579.185520362 245.0989819004 0.0))
((0 . "LWPOLYLINE") (100 . "AcDbEntity") (8 . "PLANTS") (62 . 94) (370 . 13) (100 . "AcDbPolyline") (90 . 2) (70 . 0)
(43 . 0.0) (10 7507.5417420814 286.5752262443) (10 7481.146040724 260.1809954751))
((0 . "LWPOLYLINE") (100 . "AcDbEntity") (8 . "PLANTS") (62 . 94) (370 . 13) (100 . "AcDbPolyline") (90 . 3) (70 . 0)
(43 . 0.0) (10 7488.6877828054 6896.6820135747) (10 7495.031561086 6877.8280542986) (10 7492.4582579186
6840.1209276018))
((0 . "LWPOLYLINE") (100 . "AcDbEntity") (8 . "PLANTS") (62 . 94) (370 . 13) (100 . "AcDbPolyline") (90 . 2) (70 . 0)
(43 . 0.0) (10 7488.6877828054 6896.6820135747) (10 7500 6923.0769230769))
((0 . "LWPOLYLINE") (100 . "AcDbEntity") (8 . "PLANTS") (62 . 94) (370 . 13) (100 . "AcDbPolyline") (90 . 2) (70 . 0)
(43 . 0.0) (10 7492.4582579186 6840.1209276018) (10 7511.3122171946 6828.8087104072))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7579.185520362 6915.5351809955 0.0) (10 7551.2657560714 6896.2142923778 0.0) (10 7532.8976705555
6956.093725333 0.0) (10 7500 6923.0769230769 0.0))
((0 . "LWPOLYLINE") (100 . "AcDbEntity") (8 . "PLANTS") (62 . 94) (370 . 13) (100 . "AcDbPolyline") (90 . 2) (70 . 0)
(43 . 0.0) (10 7507.5417420814 309.1996606335) (10 7500 309.1996606335))
((0 . "LWPOLYLINE") (100 . "AcDbEntity") (8 . "PLANTS") (62 . 94) (370 . 13) (100 . "AcDbPolyline") (90 . 3) (70 . 0)
(43 . 0.0) (10 7522.6244343891 339.3665158371) (10 7504.8269230769 327.8996606335) (10 7500 309.1996606335))
((0 . "LWPOLYLINE") (100 . "AcDbEntity") (8 . "PLANTS") (62 . 94) (370 . 13) (100 . "AcDbPolyline") (90 . 3) (70 . 0)
(43 . 0.0) (10 7503.7704751131 7070.1357466063) (10 7547.8152714932 6994.7207013575) (10 7545.2488687783
6972.0962669683))
((0 . "LWPOLYLINE") (100 . "AcDbEntity") (8 . "PLANTS") (62 . 94) (370 . 13) (100 . "AcDbPolyline") (90 . 2) (70 . 0)
(43 . 0.0) (10 7564.1028280543 6776.0180995475) (10 7503.7704751131 6779.7885746606))
((0 . "LWPOLYLINE") (100 . "AcDbEntity") (8 . "PLANTS") (62 . 94) (370 . 13) (100 . "AcDbPolyline") (90 . 3) (70 . 0)
(43 . 0.0) (10 7503.7704751131 6779.7885746606) (10 7503.9182126697 6798.6425339367) (10 7511.3122171946
6828.8087104072))
((0 . "LWPOLYLINE") (100 . "AcDbEntity") (8 . "PLANTS") (62 . 94) (370 . 13) (100 . "AcDbPolyline") (90 . 2) (70 . 0)
(43 . 0.0) (10 7511.3122171946 392.1578054299) (10 7503.7704751131 411.0096153846))
((0 . "LWPOLYLINE") (100 . "AcDbEntity") (8 . "PLANTS") (62 . 94) (370 . 13) (100 . "AcDbPolyline") (90 . 2) (70 . 0)
(43 . 0.0) (10 7507.5417420814 286.5752262443) (10 7507.5417420814 309.1996606335))
((0 . "LWPOLYLINE") (100 . "AcDbEntity") (8 . "PLANTS") (62 . 94) (370 . 13) (100 . "AcDbPolyline") (90 . 3) (70 . 0)
(43 . 0.0) (10 7507.5417420814 309.1996606335) (10 7525.3385746606 324.2845022624) (10 7530.1661764706 339.3665158371))
((0 . "LWPOLYLINE") (100 . "AcDbEntity") (8 . "PLANTS") (62 . 94) (370 . 13) (100 . "AcDbPolyline") (90 . 2) (70 . 0)
(43 . 0.0) (10 7507.5417420814 286.5752262443) (10 7533.9366515837 279.0356334842))
((0 . "LWPOLYLINE") (100 . "AcDbEntity") (8 . "PLANTS") (62 . 94) (370 . 13) (100 . "AcDbPolyline") (90 . 3) (70 . 0)
(43 . 0.0) (10 7511.3122171946 6828.8087104072) (10 7526.3949095023 6833.6286199095) (10 7586.7279411765
6874.0575791855))
((0 . "LWPOLYLINE") (100 . "AcDbEntity") (8 . "PLANTS") (62 . 94) (370 . 13) (100 . "AcDbPolyline") (90 . 2) (70 . 0)
(43 . 0.0) (10 7511.3122171946 392.1578054299) (10 7545.2488687783 399.69739819))
((0 . "LWPOLYLINE") (100 . "AcDbEntity") (8 . "PLANTS") (62 . 94) (370 . 13) (100 . "AcDbPolyline") (90 . 2) (70 . 0)
(43 . 0.0) (10 7518.853959276 550.5288461538) (10 7528.2805429864 552.4123303167))
((0 . "LWPOLYLINE") (100 . "AcDbEntity") (8 . "PLANTS") (62 . 94) (370 . 13) (100 . "AcDbPolyline") (90 . 3) (70 . 0)
(43 . 0.0) (10 7522.6244343891 339.3665158371) (10 7518.853959276 343.1363122172) (10 7518.853959276 354.4485294118))
((0 . "LWPOLYLINE") (100 . "AcDbEntity") (8 . "PLANTS") (62 . 94) (370 . 13) (100 . "AcDbPolyline") (90 . 2) (70 . 0)
(43 . 0.0) (10 7522.6244343891 490.1951357466) (10 7549.0193438914 418.5520361991))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4902197825) (40
. 1) (40 . 1) (40 . 1) (40 . 1) (10 7522.6244343891 490.1951357467 0.0) (10 7537.9042960189 508.88942342 0.0) (10
7576.6586295602 539.1574247088 0.0) (10 7606.7223282702 577.980713944 0.0) (10 7624.4343891402 595.8887590384 0.0))
((0 . "LWPOLYLINE") (100 . "AcDbEntity") (8 . "PLANTS") (62 . 94) (370 . 13) (100 . "AcDbPolyline") (90 . 3) (70 . 0)
(43 . 0.0) (10 7624.4343891403 644.4355160197) (10 7620.6645927602 644.6486425339) (10 7586.7279411765 629.7143665158))
((0 . "LWPOLYLINE") (100 . "AcDbEntity") (8 . "PLANTS") (62 . 94) (370 . 13) (100 . "AcDbPolyline") (90 . 2) (70 . 0)
(43 . 0.0) (10 7522.6244343891 339.3665158371) (10 7530.1661764706 339.3665158371))
((0 . "LWPOLYLINE") (100 . "AcDbEntity") (8 . "PLANTS") (62 . 94) (370 . 13) (100 . "AcDbPolyline") (90 . 3) (70 . 0)
(43 . 0.0) (10 7530.2566380746 6679.9861545926) (10 7535.1408371041 6696.8325791855) (10 7552.7906108597
6715.6865384615))
((0 . "LWPOLYLINE") (100 . "AcDbEntity") (8 . "PLANTS") (62 . 94) (370 . 13) (100 . "AcDbPolyline") (90 . 3) (70 . 0)
(43 . 0.0) (10 7624.4343891403 729.3642996654) (10 7616.8919683258 731.5174208145) (10 7559.0039776273 731.4087922619))
((0 . "LWPOLYLINE") (100 . "AcDbEntity") (8 . "PLANTS") (62 . 94) (370 . 13) (100 . "AcDbPolyline") (90 . 2) (70 . 0)
(43 . 0.0) (10 7526.3949095023 539.2166289593) (10 7528.2805429864 552.4123303167))
((0 . "LWPOLYLINE") (100 . "AcDbEntity") (8 . "PLANTS") (62 . 94) (370 . 13) (100 . "AcDbPolyline") (90 . 2) (70 . 0)
(43 . 0.0) (10 7528.2805429864 552.4123303167) (10 7533.9366515837 569.3806561086))
((0 . "LWPOLYLINE") (100 . "AcDbEntity") (8 . "PLANTS") (62 . 94) (370 . 13) (100 . "AcDbPolyline") (90 . 2) (70 . 0)
(43 . 0.0) (10 7545.2488687783 558.068438914) (10 7528.2805429864 552.4123303167))
((0 . "LWPOLYLINE") (100 . "AcDbEntity") (8 . "PLANTS") (62 . 94) (370 . 13) (100 . "AcDbPolyline") (90 . 2) (70 . 0)
(43 . 0.0) (10 7565.9876696833 352.5650452489) (10 7530.1661764706 339.3665158371))
((0 . "LWPOLYLINE") (100 . "AcDbEntity") (8 . "PLANTS") (62 . 94) (370 . 13) (100 . "AcDbPolyline") (90 . 2) (70 . 0)
(43 . 0.0) (10 7541.4783936652 6889.1402714932) (10 7533.9366515837 6885.3697963801))
((0 . "LWPOLYLINE") (100 . "AcDbEntity") (8 . "PLANTS") (62 . 94) (370 . 13) (100 . "AcDbPolyline") (90 . 2) (70 . 0)
(43 . 0.0) (10 7533.9366515837 6738.3109728507) (10 7552.7906108597 6723.2274886878))
((0 . "LWPOLYLINE") (100 . "AcDbEntity") (8 . "PLANTS") (62 . 94) (370 . 13) (100 . "AcDbPolyline") (90 . 2) (70 . 0)
(43 . 0.0) (10 7550.439180869 6481.2657332327) (10 7631.9768099548 6478.129638009))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7577.2998868778 6570.5125565611 0.0) (10 7596.4737881494 6550.9643651856 0.0) (10 7574.4776349266
6512.3157643868 0.0) (10 7545.7920168068 6527.0224255371 0.0))
((0 . "LWPOLYLINE") (100 . "AcDbEntity") (8 . "PLANTS") (62 . 94) (370 . 13) (100 . "AcDbPolyline") (90 . 3) (70 . 0)
(43 . 0.0) (10 7579.185520362 6926.84739819) (10 7550.0757918552 6960.7840497738) (10 7545.2488687783 6972.0962669683))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7565.9876696833 352.5650452489 0.0) (10 7548.2046308636 362.8919237138 0.0) (10 7561.398172546
388.4562997222 0.0) (10 7545.2488687783 399.69739819 0.0))
((0 . "LWPOLYLINE") (100 . "AcDbEntity") (8 . "PLANTS") (62 . 94) (370 . 13) (100 . "AcDbPolyline") (90 . 2) (70 . 0)
(43 . 0.0) (10 7549.0193438914 418.5520361991) (10 7545.2488687783 399.69739819))
((0 . "LWPOLYLINE") (100 . "AcDbEntity") (8 . "PLANTS") (62 . 94) (370 . 13) (100 . "AcDbPolyline") (90 . 2) (70 . 0)
(43 . 0.0) (10 7615.0979045464 822.0220588235) (10 7624.4343891403 822.0220588235))
((0 . "LWPOLYLINE") (100 . "AcDbEntity") (8 . "PLANTS") (62 . 94) (370 . 13) (100 . "AcDbPolyline") (90 . 3) (70 . 0)
(43 . 0.0) (10 7586.7279411765 629.7143665158) (10 7582.8020361991 610.8597285068) (10 7549.0193438914 584.4654977376))
((0 . "LWPOLYLINE") (100 . "AcDbEntity") (8 . "PLANTS") (62 . 94) (370 . 13) (100 . "AcDbPolyline") (90 . 2) (70 . 0)
(43 . 0.0) (10 7579.185520362 418.5520361991) (10 7549.0193438914 418.5520361991))
((0 . "LWPOLYLINE") (100 . "AcDbEntity") (8 . "PLANTS") (62 . 94) (370 . 13) (100 . "AcDbPolyline") (90 . 2) (70 . 0)
(43 . 0.0) (10 7552.7906108597 6715.6865384615) (10 7552.7906108597 6723.2274886878))
((0 . "LWPOLYLINE") (100 . "AcDbEntity") (8 . "PLANTS") (62 . 94) (370 . 13) (100 . "AcDbPolyline") (90 . 2) (70 . 0)
(43 . 0.0) (10 7575.4150452489 6734.5397058824) (10 7552.7906108597 6723.2274886878))
((0 . "LWPOLYLINE") (100 . "AcDbEntity") (8 . "PLANTS") (62 . 94) (370 . 13) (100 . "AcDbPolyline") (90 . 3) (70 . 0)
(43 . 0.0) (10 7609.3523755656 6711.9152714932) (10 7579.185520362 6693.3647058824) (10 7552.7906108597
6715.6865384615))
((0 . "LWPOLYLINE") (100 . "AcDbEntity") (8 . "PLANTS") (62 . 94) (370 . 13) (100 . "AcDbPolyline") (90 . 2) (70 . 0)
(43 . 0.0) (10 7577.2998868778 6570.5125565611) (10 7540.5974036698 6578.1693856553))
((0 . "LWPOLYLINE") (100 . "AcDbEntity") (8 . "PLANTS") (62 . 94) (370 . 13) (100 . "AcDbPolyline") (90 . 3) (70 . 0)
(43 . 0.0) (10 7538.2902936331 6600.8855460172) (10 7547.8214932127 6613.8765837104) (10 7552.7906108597
6628.9592760181))
((0 . "LWPOLYLINE") (100 . "AcDbEntity") (8 . "PLANTS") (62 . 94) (370 . 13) (100 . "AcDbPolyline") (90 . 3) (70 . 0)
(43 . 0.0) (10 7560.331561086 267.7234162896) (10 7564.1028280543 263.9507918552) (10 7575.4150452489 263.9507918552))
((0 . "LWPOLYLINE") (100 . "AcDbEntity") (8 . "PLANTS") (62 . 94) (370 . 13) (100 . "AcDbPolyline") (90 . 2) (70 . 0)
(43 . 0.0) (10 7575.4150452489 6772.2476244344) (10 7564.1028280543 6776.0180995475))
((0 . "LWPOLYLINE") (100 . "AcDbEntity") (8 . "PLANTS") (62 . 94) (370 . 13) (100 . "AcDbPolyline") (90 . 3) (70 . 0)
(43 . 0.0) (10 7564.1028280543 6776.0180995475) (10 7568.9296380091 6806.1842760181) (10 7586.7279411765
6828.8087104072))
((0 . "LWPOLYLINE") (100 . "AcDbEntity") (8 . "PLANTS") (62 . 94) (370 . 13) (100 . "AcDbPolyline") (90 . 3) (70 . 0)
(43 . 0.0) (10 7579.185520362 316.742081448) (10 7572.834841629 320.6671945701) (10 7565.9876696833 352.5650452489))
((0 . "LWPOLYLINE") (100 . "AcDbEntity") (8 . "PLANTS") (62 . 94) (370 . 13) (100 . "AcDbPolyline") (90 . 3) (70 . 0)
(43 . 0.0) (10 7565.9876696833 352.5650452489) (10 7571.6437782805 358.2211538462) (10 7582.9553167421 358.2211538462))
((0 . "LWPOLYLINE") (100 . "AcDbEntity") (8 . "PLANTS") (62 . 94) (370 . 13) (100 . "AcDbPolyline") (90 . 2) (70 . 0)
(43 . 0.0) (10 7571.6437782805 6987.1797511312) (10 7579.185520362 6983.4084841629))
((0 . "LWPOLYLINE") (100 . "AcDbEntity") (8 . "PLANTS") (62 . 94) (370 . 13) (100 . "AcDbPolyline") (90 . 2) (70 . 0)
(43 . 0.0) (10 7575.4150452489 6772.2476244344) (10 7575.4150452489 6734.5397058824))
((0 . "LWPOLYLINE") (100 . "AcDbEntity") (8 . "PLANTS") (62 . 94) (370 . 13) (100 . "AcDbPolyline") (90 . 2) (70 . 0)
(43 . 0.0) (10 7575.4150452489 6772.2476244344) (10 7635.7466063348 6779.7885746606))
((0 . "LWPOLYLINE") (100 . "AcDbEntity") (8 . "PLANTS") (62 . 94) (370 . 13) (100 . "AcDbPolyline") (90 . 2) (70 . 0)
(43 . 0.0) (10 7609.3523755656 6723.2274886878) (10 7575.4150452489 6734.5397058824))
((0 . "LWPOLYLINE") (100 . "AcDbEntity") (8 . "PLANTS") (62 . 94) (370 . 13) (100 . "AcDbPolyline") (90 . 2) (70 . 0)
(43 . 0.0) (10 7575.4150452489 263.9507918552) (10 7579.185520362 245.0989819005))
((0 . "LWPOLYLINE") (100 . "AcDbEntity") (8 . "PLANTS") (62 . 94) (370 . 13) (100 . "AcDbPolyline") (90 . 3) (70 . 0)
(43 . 0.0) (10 7575.4150452489 263.9507918552) (10 7579.0377828054 271.5001131222) (10 7579.185520362 316.742081448))
((0 . "LWPOLYLINE") (100 . "AcDbEntity") (8 . "PLANTS") (62 . 94) (370 . 13) (100 . "AcDbPolyline") (90 . 2) (70 . 0)
(43 . 0.0) (10 7579.185520362 6598.7930995475) (10 7577.2998868778 6570.5125565611))
((0 . "LWPOLYLINE") (100 . "AcDbEntity") (8 . "PLANTS") (62 . 94) (370 . 13) (100 . "AcDbPolyline") (90 . 3) (70 . 0)
(43 . 0.0) (10 7577.2998868778 6570.5125565611) (10 7594.2675339367 6577.2251131222) (10 7605.5797511312
6591.2521493213))
((0 . "LWPOLYLINE") (100 . "AcDbEntity") (8 . "PLANTS") (62 . 94) (370 . 13) (100 . "AcDbPolyline") (90 . 3) (70 . 0)
(43 . 0.0) (10 7579.185520362 6983.4084841629) (10 7598.1872171946 6953.2496606335) (10 7609.3523755656
6945.7013574661))
((0 . "LWPOLYLINE") (100 . "AcDbEntity") (8 . "PLANTS") (62 . 94) (370 . 13) (100 . "AcDbPolyline") (90 . 3) (70 . 0)
(43 . 0.0) (10 7582.9553167421 6998.4919683258) (10 7582.9553167421 6987.1797511312) (10 7579.185520362
6983.4084841629))
((0 . "LWPOLYLINE") (100 . "AcDbEntity") (8 . "PLANTS") (62 . 94) (370 . 13) (100 . "AcDbPolyline") (90 . 2) (70 . 0)
(43 . 0.0) (10 7579.185520362 6915.5351809955) (10 7579.185520362 6926.84739819))
((0 . "LWPOLYLINE") (100 . "AcDbEntity") (8 . "PLANTS") (62 . 94) (370 . 13) (100 . "AcDbPolyline") (90 . 2) (70 . 0)
(43 . 0.0) (10 7579.185520362 6926.84739819) (10 7609.3523755656 6938.1596153846))
((0 . "LWPOLYLINE") (100 . "AcDbEntity") (8 . "PLANTS") (62 . 94) (370 . 13) (100 . "AcDbPolyline") (90 . 2) (70 . 0)
(43 . 0.0) (10 7579.185520362 6915.5351809955) (10 7586.7279411765 6874.0575791855))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7579.185520362 418.5520361991 0.0) (10 7596.5358848446 402.9905316059 0.0) (10 7593.7258348115
376.2483498836 0.0) (10 7582.9553167421 358.2211538462 0.0))
((0 . "LWPOLYLINE") (100 . "AcDbEntity") (8 . "PLANTS") (62 . 94) (370 . 13) (100 . "AcDbPolyline") (90 . 3) (70 . 0)
(43 . 0.0) (10 7579.185520362 418.5520361991) (10 7598.1872171946 448.5635746606) (10 7613.1221719457 452.4886877828))
((0 . "LWPOLYLINE") (100 . "AcDbEntity") (8 . "PLANTS") (62 . 94) (370 . 13) (100 . "AcDbPolyline") (90 . 3) (70 . 0)
(43 . 0.0) (10 7579.185520362 316.742081448) (10 7593.0641402715 328.0542986425) (10 7594.2675339367 339.3665158371))
((0 . "LWPOLYLINE") (100 . "AcDbEntity") (8 . "PLANTS") (62 . 94) (370 . 13) (100 . "AcDbPolyline") (90 . 2) (70 . 0)
(43 . 0.0) (10 7631.9768099548 245.0989819005) (10 7579.185520362 245.0989819005))
((0 . "LWPOLYLINE") (100 . "AcDbEntity") (8 . "PLANTS") (62 . 94) (370 . 13) (100 . "AcDbPolyline") (90 . 2) (70 . 0)
(43 . 0.0) (10 7582.9553167421 6998.4919683258) (10 7616.8919683258 6998.4919683258))
((0 . "LWPOLYLINE") (100 . "AcDbEntity") (8 . "PLANTS") (62 . 94) (370 . 13) (100 . "AcDbPolyline") (90 . 3) (70 . 0)
(43 . 0.0) (10 7582.9553167421 6998.4919683258) (10 7575.5634615385 7032.4286199095) (10 7586.7279411765
7055.0530542986))
((0 . "LWPOLYLINE") (100 . "AcDbEntity") (8 . "PLANTS") (62 . 94) (370 . 13) (100 . "AcDbPolyline") (90 . 2) (70 . 0)
(43 . 0.0) (10 7582.9553167421 358.2211538462) (10 7594.2675339367 339.3665158371))
((0 . "LWPOLYLINE") (100 . "AcDbEntity") (8 . "PLANTS") (62 . 94) (370 . 13) (100 . "AcDbPolyline") (90 . 2) (70 . 0)
(43 . 0.0) (10 7635.7466063348 6866.5158371041) (10 7586.7279411765 6874.0575791855))
((0 . "LWPOLYLINE") (100 . "AcDbEntity") (8 . "PLANTS") (62 . 94) (370 . 13) (100 . "AcDbPolyline") (90 . 3) (70 . 0)
(43 . 0.0) (10 7594.2675339367 6632.7297511312) (10 7601.8168552036 6646.7564479638) (10 7624.4343891403
6651.5837104072))
((0 . "LWPOLYLINE") (100 . "AcDbEntity") (8 . "PLANTS") (62 . 94) (370 . 13) (100 . "AcDbPolyline") (90 . 2) (70 . 0)
(43 . 0.0) (10 7601.8099547511 343.1363122172) (10 7594.2675339367 339.3665158371))
((0 . "LWPOLYLINE") (100 . "AcDbEntity") (8 . "PLANTS") (62 . 94) (370 . 13) (100 . "AcDbPolyline") (90 . 2) (70 . 0)
(43 . 0.0) (10 7616.8919683258 7006.032918552) (10 7609.3523755656 7036.1990950226))
((0 . "LWPOLYLINE") (100 . "AcDbEntity") (8 . "PLANTS") (62 . 94) (370 . 13) (100 . "AcDbPolyline") (90 . 2) (70 . 0)
(43 . 0.0) (10 7609.3523755656 6938.1596153846) (10 7609.3523755656 6945.7013574661))
((0 . "LWPOLYLINE") (100 . "AcDbEntity") (8 . "PLANTS") (62 . 94) (370 . 13) (100 . "AcDbPolyline") (90 . 3) (70 . 0)
(43 . 0.0) (10 7616.8919683258 6998.4919683258) (10 7616.7386877828 6957.0135746606) (10 7609.3523755656
6945.7013574661))
((0 . "LWPOLYLINE") (100 . "AcDbEntity") (8 . "PLANTS") (62 . 94) (370 . 13) (100 . "AcDbPolyline") (90 . 2) (70 . 0)
(43 . 0.0) (10 7669.6832579186 6930.6186651584) (10 7609.3523755656 6938.1596153846))
((0 . "LWPOLYLINE") (100 . "AcDbEntity") (8 . "PLANTS") (62 . 94) (370 . 13) (100 . "AcDbPolyline") (90 . 2) (70 . 0)
(43 . 0.0) (10 7609.3523755656 6711.9152714932) (10 7609.3523755656 6723.2274886878))
((0 . "LWPOLYLINE") (100 . "AcDbEntity") (8 . "PLANTS") (62 . 94) (370 . 13) (100 . "AcDbPolyline") (90 . 3) (70 . 0)
(43 . 0.0) (10 7609.3523755656 6723.2274886878) (10 7623.3780542986 6734.5400452489) (10 7635.7466063348
6772.2476244344))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7609.3523755656 6711.9152714932 0.0) (10 7632.8273753087 6702.6096673081 0.0) (10 7633.2378308751
6671.6300612766 0.0) (10 7624.4343891403 6651.5837104072 0.0))
((0 . "LWPOLYLINE") (100 . "AcDbEntity") (8 . "PLANTS") (62 . 94) (370 . 13) (100 . "AcDbPolyline") (90 . 3) (70 . 0)
(43 . 0.0) (10 7609.3523755656 6414.0271493213) (10 7618.0906108597 6432.7260180995) (10 7628.2041855204
6436.6515837104))
((0 . "LWPOLYLINE") (100 . "AcDbEntity") (8 . "PLANTS") (62 . 94) (370 . 13) (100 . "AcDbPolyline") (90 . 2) (70 . 0)
(43 . 0.0) (10 7616.8919683258 429.8642533937) (10 7613.1221719457 452.4886877828))
((0 . "LWPOLYLINE") (100 . "AcDbEntity") (8 . "PLANTS") (62 . 94) (370 . 13) (100 . "AcDbPolyline") (90 . 3) (70 . 0)
(43 . 0.0) (10 7631.9768099548 467.5707013575) (10 7617.0472850679 459.888800905) (10 7613.1221719457 452.4886877828))
((0 . "LWPOLYLINE") (100 . "AcDbEntity") (8 . "PLANTS") (62 . 94) (370 . 13) (100 . "AcDbPolyline") (90 . 2) (70 . 0)
(43 . 0.0) (10 7639.5164027149 7006.032918552) (10 7616.8919683258 7006.032918552))
((0 . "LWPOLYLINE") (100 . "AcDbEntity") (8 . "PLANTS") (62 . 94) (370 . 13) (100 . "AcDbPolyline") (90 . 2) (70 . 0)
(43 . 0.0) (10 7616.8919683258 6998.4919683258) (10 7616.8919683258 7006.032918552))
((0 . "SPLINE") (100 . "AcDbEntity") (8 . "PLANTS") (62 . 94) (370 . 13) (100 . "AcDbSpline") (70 . 0) (71 . 3) (72 .
12) (73 . 8) (74 . 0) (42 . 0.0000001) (43 . 0.0000001) (40 . 0.0) (40 . 0.0) (40 . 0.0) (40 . 0.0) (40 . 0.4596208273)
(40 . 0.5273988338) (40 . 0.684584886) (40 . 0.7731820058) (40 . 1) (40 . 1) (40 . 1) (40 . 1) (10 7639.5164027149
7006.032918552 0.0) (10 7651.8138036609 7024.483810726 0.0) (10 7666.2552053038 7081.6621441681 0.0) (10 7631.6812170497
7091.76129655 0.0) (10 7610.0100946673 7079.2569386566 0.0) (10 7596.6410963221 7099.785367112 0.0) (10 7610.2913496625
7127.6963270053 0.0) (10 7620.6645927602 7130.4673076923 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4551883055) (40
. 1) (40 . 1) (40 . 1) (40 . 1) (10 7665.9134615385 6595.0226244344 0.0) (10 7651.1635371609 6593.2848217628 0.0) (10
7617.2779520804 6601.8257355534 0.0) (10 7636.5642700118 6639.3377772163 0.0) (10 7624.4343891403 6651.5837104073 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7647.0588235294 414.782239819 0.0) (10 7619.1111383057 414.2316372894 0.0) (10 7606.3517897679
365.262111738 0.0) (10 7624.4343891402 346.9089366516 0.0))
((0 . "LWPOLYLINE") (100 . "AcDbEntity") (8 . "PLANTS") (62 . 94) (370 . 13) (100 . "AcDbPolyline") (90 . 3) (70 . 0)
(43 . 0.0) (10 7635.7466063348 297.8874434389) (10 7629.4028280543 301.8133484163) (10 7624.4343891403 331.8240950226))
((0 . "LWPOLYLINE") (100 . "AcDbEntity") (8 . "PLANTS") (62 . 94) (370 . 13) (100 . "AcDbPolyline") (90 . 2) (70 . 0)
(43 . 0.0) (10 7628.2041855204 6436.6515837104) (10 7665.9134615385 6429.1101809955))
((0 . "LWPOLYLINE") (100 . "AcDbEntity") (8 . "PLANTS") (62 . 94) (370 . 13) (100 . "AcDbPolyline") (90 . 2) (70 . 0)
(43 . 0.0) (10 7631.9768099548 6478.129638009) (10 7628.2041855204 6436.6515837104))
((0 . "LWPOLYLINE") (100 . "AcDbEntity") (8 . "PLANTS") (62 . 94) (370 . 13) (100 . "AcDbPolyline") (90 . 3) (70 . 0)
(43 . 0.0) (10 7639.5164027149 6342.3830316742) (10 7625.6392533937 6353.6955882353) (10 7628.2041855204
6372.5490950226))
((0 . "LWPOLYLINE") (100 . "AcDbEntity") (8 . "PLANTS") (62 . 94) (370 . 13) (100 . "AcDbPolyline") (90 . 2) (70 . 0)
(43 . 0.0) (10 7631.9768099548 6478.129638009) (10 7650.8286199095 6481.9004524887))
((0 . "LWPOLYLINE") (100 . "AcDbEntity") (8 . "PLANTS") (62 . 94) (370 . 13) (100 . "AcDbPolyline") (90 . 2) (70 . 0)
(43 . 0.0) (10 7631.9768099548 6274.5097285068) (10 7639.5164027149 6297.1341628959))
((0 . "LWPOLYLINE") (100 . "AcDbEntity") (8 . "PLANTS") (62 . 94) (370 . 13) (100 . "AcDbPolyline") (90 . 2) (70 . 0)
(43 . 0.0) (10 7631.9768099548 467.5707013575) (10 7639.5164027149 463.8009049774))
((0 . "LWPOLYLINE") (100 . "AcDbEntity") (8 . "PLANTS") (62 . 94) (370 . 13) (100 . "AcDbPolyline") (90 . 2) (70 . 0)
(43 . 0.0) (10 7631.9768099548 467.5707013575) (10 7635.7466063348 475.1131221719))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7631.9768099548 245.0989819005 0.0) (10 7655.79603463 218.064144456 0.0) (10 7698.6324032919
224.7773515623 0.0) (10 7726.2443438914 241.3263574661 0.0))
((0 . "LWPOLYLINE") (100 . "AcDbEntity") (8 . "PLANTS") (62 . 94) (370 . 13) (100 . "AcDbPolyline") (90 . 2) (70 . 0)
(43 . 0.0) (10 7631.9768099548 245.0989819005) (10 7635.7466063348 297.8874434389))
((0 . "LWPOLYLINE") (100 . "AcDbEntity") (8 . "PLANTS") (62 . 94) (370 . 13) (100 . "AcDbPolyline") (90 . 2) (70 . 0)
(43 . 0.0) (10 7647.0588235294 6866.5158371041) (10 7635.7466063348 6866.5158371041))
((0 . "LWPOLYLINE") (100 . "AcDbEntity") (8 . "PLANTS") (62 . 94) (370 . 13) (100 . "AcDbPolyline") (90 . 3) (70 . 0)
(43 . 0.0) (10 7639.5164027149 6794.8720588235) (10 7635.8943438914 6802.4199095023) (10 7635.7466063348
6866.5158371041))
((0 . "LWPOLYLINE") (100 . "AcDbEntity") (8 . "PLANTS") (62 . 94) (370 . 13) (100 . "AcDbPolyline") (90 . 2) (70 . 0)
(43 . 0.0) (10 7635.7466063348 6779.7885746606) (10 7635.7466063348 6772.2476244344))
((0 . "LWPOLYLINE") (100 . "AcDbEntity") (8 . "PLANTS") (62 . 94) (370 . 13) (100 . "AcDbPolyline") (90 . 3) (70 . 0)
(43 . 0.0) (10 7639.5164027149 6794.8720588235) (10 7639.5164027149 6783.559841629) (10 7635.7466063348
6779.7885746606))
((0 . "LWPOLYLINE") (100 . "AcDbEntity") (8 . "PLANTS") (62 . 94) (370 . 13) (100 . "AcDbPolyline") (90 . 2) (70 . 0)
(43 . 0.0) (10 7665.9134615385 6768.4763574661) (10 7635.7466063348 6772.2476244344))
((0 . "LWPOLYLINE") (100 . "AcDbEntity") (8 . "PLANTS") (62 . 94) (370 . 13) (100 . "AcDbPolyline") (90 . 3) (70 . 0)
(43 . 0.0) (10 7635.7466063348 297.8874434389) (10 7649.6314479638 309.1996606335) (10 7665.9134615385 369.5333710407))
((0 . "LWPOLYLINE") (100 . "AcDbEntity") (8 . "PLANTS") (62 . 94) (370 . 13) (100 . "AcDbPolyline") (90 . 3) (70 . 0)
(43 . 0.0) (10 7639.5164027149 7006.032918552) (10 7651.8857466063 6987.3272624434) (10 7669.6832579186
6972.0962669683))
((0 . "LWPOLYLINE") (100 . "AcDbEntity") (8 . "PLANTS") (62 . 94) (370 . 13) (100 . "AcDbPolyline") (90 . 3) (70 . 0)
(43 . 0.0) (10 7639.5164027149 6794.8720588235) (10 7665.9058823529 6797.4382352941) (10 7680.9954751131
6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7650.8286199095 6500.7540723982 0.0) (10 7632.7130560678 6515.5390587617 0.0) (10 7625.3608900623
6544.4392657311 0.0) (10 7639.5164027149 6564.8564479638 0.0))
((0 . "LWPOLYLINE") (100 . "AcDbEntity") (8 . "PLANTS") (62 . 94) (370 . 13) (100 . "AcDbPolyline") (90 . 3) (70 . 0)
(43 . 0.0) (10 7703.6199095023 6858.9740950226) (10 7654.6061085973 6859.128959276) (10 7647.0588235294
6866.5158371041))
((0 . "LWPOLYLINE") (100 . "AcDbEntity") (8 . "PLANTS") (62 . 94) (370 . 13) (100 . "AcDbPolyline") (90 . 3) (70 . 0)
(43 . 0.0) (10 7673.4530542986 6923.0769230769) (10 7659.5690045249 6907.9942307692) (10 7647.0588235294
6866.5158371041))
((0 . "LWPOLYLINE") (100 . "AcDbEntity") (8 . "PLANTS") (62 . 94) (370 . 13) (100 . "AcDbPolyline") (90 . 3) (70 . 0)
(43 . 0.0) (10 7665.9134615385 369.5333710407) (10 7655.7984162896 380.8455882353) (10 7647.0588235294 414.782239819))
((0 . "LWPOLYLINE") (100 . "AcDbEntity") (8 . "PLANTS") (62 . 94) (370 . 13) (100 . "AcDbPolyline") (90 . 3) (70 . 0)
(43 . 0.0) (10 7650.8286199095 429.8642533937) (10 7647.0588235294 426.0944570136) (10 7647.0588235294 414.782239819))
((0 . "LWPOLYLINE") (100 . "AcDbEntity") (8 . "PLANTS") (62 . 94) (370 . 13) (100 . "AcDbPolyline") (90 . 2) (70 . 0)
(43 . 0.0) (10 7650.8286199095 6693.0621040724) (10 7669.6832579186 6700.6030542986))
((0 . "LWPOLYLINE") (100 . "AcDbEntity") (8 . "PLANTS") (62 . 94) (370 . 13) (100 . "AcDbPolyline") (90 . 2) (70 . 0)
(43 . 0.0) (10 7650.8286199095 6500.7540723982) (10 7650.8286199095 6481.9004524887))
((0 . "LWPOLYLINE") (100 . "AcDbEntity") (8 . "PLANTS") (62 . 94) (370 . 13) (100 . "AcDbPolyline") (90 . 3) (70 . 0)
(43 . 0.0) (10 7673.4530542986 6534.6910633484) (10 7668.4852941176 6519.6075791855) (10 7650.8286199095
6500.7540723982))
((0 . "LWPOLYLINE") (100 . "AcDbEntity") (8 . "PLANTS") (62 . 94) (370 . 13) (100 . "AcDbPolyline") (90 . 2) (70 . 0)
(43 . 0.0) (10 7669.6832579186 6474.3590497738) (10 7650.8286199095 6481.9004524887))
((0 . "LWPOLYLINE") (100 . "AcDbEntity") (8 . "PLANTS") (62 . 94) (370 . 13) (100 . "AcDbPolyline") (90 . 2) (70 . 0)
(43 . 0.0) (10 7673.4530542986 6711.9152714932) (10 7665.9134615385 6768.4763574661))
((0 . "LWPOLYLINE") (100 . "AcDbEntity") (8 . "PLANTS") (62 . 94) (370 . 13) (100 . "AcDbPolyline") (90 . 2) (70 . 0)
(43 . 0.0) (10 7665.9134615385 6768.4763574661) (10 7680.9954751131 6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7673.4530542986 6534.6910633484 0.0) (10 7661.1174039101 6552.5011927365 0.0) (10 7676.5339267405
6576.2519608271 0.0) (10 7665.9134615385 6595.0226244344 0.0))
((0 . "LWPOLYLINE") (100 . "AcDbEntity") (8 . "PLANTS") (62 . 94) (370 . 13) (100 . "AcDbPolyline") (90 . 3) (70 . 0)
(43 . 0.0) (10 7669.6832579186 6659.1254524887) (10 7666.060520362 6655.1997737557) (10 7665.9134615385
6595.0226244344))
((0 . "LWPOLYLINE") (100 . "AcDbEntity") (8 . "PLANTS") (62 . 94) (370 . 13) (100 . "AcDbPolyline") (90 . 2) (70 . 0)
(43 . 0.0) (10 7665.9134615385 6429.1101809955) (10 7669.6832579186 6421.5685520362))
((0 . "LWPOLYLINE") (100 . "AcDbEntity") (8 . "PLANTS") (62 . 94) (370 . 13) (100 . "AcDbPolyline") (90 . 2) (70 . 0)
(43 . 0.0) (10 7669.6832579186 6474.3590497738) (10 7665.9134615385 6429.1101809955))
((0 . "SPLINE") (100 . "AcDbEntity") (8 . "PLANTS") (62 . 94) (370 . 13) (100 . "AcDbSpline") (70 . 0) (71 . 3) (72 .
12) (73 . 8) (74 . 0) (42 . 0.0000001) (43 . 0.0000001) (40 . 0.0) (40 . 0.0) (40 . 0.0) (40 . 0.0) (40 . 0.3004705273)
(40 . 0.6254053937) (40 . 0.7060602438) (40 . 0.8545856105) (40 . 1) (40 . 1) (40 . 1) (40 . 1) (10 7684.7652714932
279.0356334842 0.0) (10 7678.9246628061 305.9253317407 0.0) (10 7707.0093701067 334.4884991158 0.0) (10 7743.1735367662
414.6071735816 0.0) (10 7702.9540311171 421.3166349305 0.0) (10 7680.627173139 398.0033909115 0.0) (10 7677.1211596336
373.3347759223 0.0) (10 7665.9134615386 369.5333710407 0.0))
((0 . "LWPOLYLINE") (100 . "AcDbEntity") (8 . "PLANTS") (62 . 94) (370 . 13) (100 . "AcDbPolyline") (90 . 2) (70 . 0)
(43 . 0.0) (10 7669.6832579186 6930.6186651584) (10 7669.6832579186 6972.0962669683))
((0 . "LWPOLYLINE") (100 . "AcDbEntity") (8 . "PLANTS") (62 . 94) (370 . 13) (100 . "AcDbPolyline") (90 . 3) (70 . 0)
(43 . 0.0) (10 7688.5378959276 7009.8041855204) (10 7679.7906108597 6983.4088235294) (10 7669.6832579186
6972.0962669683))
((0 . "LWPOLYLINE") (100 . "AcDbEntity") (8 . "PLANTS") (62 . 94) (370 . 13) (100 . "AcDbPolyline") (90 . 2) (70 . 0)
(43 . 0.0) (10 7673.4530542986 6923.0769230769) (10 7669.6832579186 6930.6186651584))
((0 . "LWPOLYLINE") (100 . "AcDbEntity") (8 . "PLANTS") (62 . 94) (370 . 13) (100 . "AcDbPolyline") (90 . 2) (70 . 0)
(43 . 0.0) (10 7669.6832579186 6659.1254524887) (10 7669.6832579186 6700.6030542986))
((0 . "LWPOLYLINE") (100 . "AcDbEntity") (8 . "PLANTS") (62 . 94) (370 . 13) (100 . "AcDbPolyline") (90 . 2) (70 . 0)
(43 . 0.0) (10 7669.6832579186 6700.6030542986) (10 7673.4530542986 6711.9152714932))
((0 . "LWPOLYLINE") (100 . "AcDbEntity") (8 . "PLANTS") (62 . 94) (370 . 13) (100 . "AcDbPolyline") (90 . 2) (70 . 0)
(43 . 0.0) (10 7703.6199095023 6647.8132352941) (10 7669.6832579186 6659.1254524887))
((0 . "LWPOLYLINE") (100 . "AcDbEntity") (8 . "PLANTS") (62 . 94) (370 . 13) (100 . "AcDbPolyline") (90 . 2) (70 . 0)
(43 . 0.0) (10 7703.6199095023 6481.9004524887) (10 7669.6832579186 6474.3590497738))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.5566395216)
(40 . 0.6540894196) (40 . 0.7663136656) (40 . 1) (40 . 1) (40 . 1) (40 . 1) (10 7673.4530542986 6180.2414027149 0.0) (10
7663.6394892255 6224.5646140124 0.0) (10 7680.2468027329 6280.7264972373 0.0) (10 7661.8765058631 6339.7440577534 0.0)
(10 7671.3723624894 6374.3458003283 0.0) (10 7663.7431196423 6402.4639122227 0.0) (10 7669.6832579186 6421.5685520362
0.0))
((0 . "LWPOLYLINE") (100 . "AcDbEntity") (8 . "PLANTS") (62 . 94) (370 . 13) (100 . "AcDbPolyline") (90 . 3) (70 . 0)
(43 . 0.0) (10 7711.1623303167 6447.963800905) (10 7703.4652714932 6422.7729638009) (10 7669.6832579186
6421.5685520362))
((0 . "LWPOLYLINE") (100 . "AcDbEntity") (8 . "PLANTS") (62 . 94) (370 . 13) (100 . "AcDbPolyline") (90 . 2) (70 . 0)
(43 . 0.0) (10 7673.4530542986 6923.0769230769) (10 7692.3076923077 6923.0769230769))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7673.4530542986 6711.9152714932 0.0) (10 7696.4143659481 6708.8974078607 0.0) (10 7708.791172326
6738.3154994518 0.0) (10 7733.7867647059 6730.7692307692 0.0))
((0 . "LWPOLYLINE") (100 . "AcDbEntity") (8 . "PLANTS") (62 . 94) (370 . 13) (100 . "AcDbPolyline") (90 . 2) (70 . 0)
(43 . 0.0) (10 7673.4530542986 6534.6910633484) (10 7699.8501131222 6534.6910633484))
((0 . "LWPOLYLINE") (100 . "AcDbEntity") (8 . "PLANTS") (62 . 94) (370 . 13) (100 . "AcDbPolyline") (90 . 2) (70 . 0)
(43 . 0.0) (10 7684.7652714932 279.0356334842) (10 7677.225678733 267.7234162896))
((0 . "LWPOLYLINE") (100 . "AcDbEntity") (8 . "PLANTS") (62 . 94) (370 . 13) (100 . "AcDbPolyline") (90 . 2) (70 . 0)
(43 . 0.0) (10 7680.9954751131 6779.7885746606) (10 7696.0774886878 6779.7885746606))
((0 . "LWPOLYLINE") (100 . "AcDbEntity") (8 . "PLANTS") (62 . 94) (370 . 13) (100 . "AcDbPolyline") (90 . 2) (70 . 0)
(43 . 0.0) (10 7711.1623303167 279.0356334842) (10 7684.7652714932 279.0356334842))
((0 . "LWPOLYLINE") (100 . "AcDbEntity") (8 . "PLANTS") (62 . 94) (370 . 13) (100 . "AcDbPolyline") (90 . 2) (70 . 0)
(43 . 0.0) (10 7688.5390337153 7139.4590139568) (10 7688.5378959276 7009.8041855204))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.6863229328)
(40 . 0.8439358329) (40 . 1) (40 . 1) (40 . 1) (40 . 1) (10 7688.5378959276 7009.8041855204 0.0) (10 7739.8085372488
7001.592756286 0.0) (10 7771.0561813075 7084.4430092967 0.0) (10 7848.3529588888 7076.6287382403 0.0) (10
7830.4911937257 7040.5068900721 0.0) (10 7820.511877828 7039.9695701357 0.0))
((0 . "LWPOLYLINE") (100 . "AcDbEntity") (8 . "PLANTS") (62 . 94) (370 . 13) (100 . "AcDbPolyline") (90 . 3) (70 . 0)
(43 . 0.0) (10 7692.3076923077 6923.0769230769) (10 7703.4721719457 6896.6820135747) (10 7703.6199095023
6874.0575791855))
((0 . "LWPOLYLINE") (100 . "AcDbEntity") (8 . "PLANTS") (62 . 94) (370 . 13) (100 . "AcDbPolyline") (90 . 2) (70 . 0)
(43 . 0.0) (10 7699.8501131222 6926.84739819) (10 7692.3076923077 6923.0769230769))
((0 . "LWPOLYLINE") (100 . "AcDbEntity") (8 . "PLANTS") (62 . 94) (370 . 13) (100 . "AcDbPolyline") (90 . 3) (70 . 0)
(43 . 0.0) (10 7731.9004524887 6774.1324660633) (10 7703.6268099548 6772.4020361991) (10 7696.0774886878
6779.7885746606))
((0 . "LWPOLYLINE") (100 . "AcDbEntity") (8 . "PLANTS") (62 . 94) (370 . 13) (100 . "AcDbPolyline") (90 . 2) (70 . 0)
(43 . 0.0) (10 7714.9321266968 6817.4964932127) (10 7696.0774886878 6779.7885746606))
((0 . "LWPOLYLINE") (100 . "AcDbEntity") (8 . "PLANTS") (62 . 94) (370 . 13) (100 . "AcDbPolyline") (90 . 3) (70 . 0)
(43 . 0.0) (10 7696.0774886878 6346.1538461538) (10 7706.1925339367 6334.8416289593) (10 7718.7019230769
6297.1341628959))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7699.8501131222 6926.8473981901 0.0) (10 7717.0919142881 6978.6212893066 0.0) (10 7761.5854323354
7036.3904655348 0.0) (10 7820.5118778281 7039.9695701358 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7818.6283936652 6938.1596153846 0.0) (10 7776.3699271458 6973.3666011933 0.0) (10 7742.4095645992
6922.7022728014 0.0) (10 7699.8501131222 6926.84739819 0.0))
((0 . "LWPOLYLINE") (100 . "AcDbEntity") (8 . "PLANTS") (62 . 94) (370 . 13) (100 . "AcDbPolyline") (90 . 2) (70 . 0)
(43 . 0.0) (10 7703.6199095023 6481.9004524887) (10 7699.8501131222 6534.6910633484))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6666495614) (40
. 1) (40 . 1) (40 . 1) (40 . 1) (10 7703.6199095023 6647.8132352941 0.0) (10 7719.7794429218 6621.5145293645 0.0) (10
7705.0973516148 6585.0422402726 0.0) (10 7702.0397750535 6546.8076593507 0.0) (10 7699.8501131223 6534.6910633484 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7801.6600678733 6843.8914027149 0.0) (10 7765.3615157175 6846.2672767136 0.0) (10 7745.3095967499
6889.8539429586 0.0) (10 7703.6199095023 6874.0575791855 0.0))
((0 . "LWPOLYLINE") (100 . "AcDbEntity") (8 . "PLANTS") (62 . 94) (370 . 13) (100 . "AcDbPolyline") (90 . 2) (70 . 0)
(43 . 0.0) (10 7703.6199095023 6858.9740950226) (10 7703.6199095023 6874.0575791855))
((0 . "LWPOLYLINE") (100 . "AcDbEntity") (8 . "PLANTS") (62 . 94) (370 . 13) (100 . "AcDbPolyline") (90 . 2) (70 . 0)
(43 . 0.0) (10 7703.6199095023 6858.9740950226) (10 7714.9321266968 6817.4964932127))
((0 . "LWPOLYLINE") (100 . "AcDbEntity") (8 . "PLANTS") (62 . 94) (370 . 13) (100 . "AcDbPolyline") (90 . 2) (70 . 0)
(43 . 0.0) (10 7703.6199095023 6647.8132352941) (10 7711.1623303167 6647.8132352941))
((0 . "LWPOLYLINE") (100 . "AcDbEntity") (8 . "PLANTS") (62 . 94) (370 . 13) (100 . "AcDbPolyline") (90 . 2) (70 . 0)
(43 . 0.0) (10 7703.6199095023 6481.9004524887) (10 7766.366882147 6481.8957055954))
((0 . "LWPOLYLINE") (100 . "AcDbEntity") (8 . "PLANTS") (62 . 94) (370 . 13) (100 . "AcDbPolyline") (90 . 2) (70 . 0)
(43 . 0.0) (10 7711.1623303167 6647.8132352941) (10 7711.1623303167 6659.1254524887))
((0 . "LWPOLYLINE") (100 . "AcDbEntity") (8 . "PLANTS") (62 . 94) (370 . 13) (100 . "AcDbPolyline") (90 . 2) (70 . 0)
(43 . 0.0) (10 7711.1623303167 6647.8132352941) (10 7756.411199095 6636.5010180995))
((0 . "LWPOLYLINE") (100 . "AcDbEntity") (8 . "PLANTS") (62 . 94) (370 . 13) (100 . "AcDbPolyline") (90 . 3) (70 . 0)
(43 . 0.0) (10 7711.1623303167 279.0356334842) (10 7715.9884615385 260.1878959276) (10 7726.2443438914 252.6385746606))
((0 . "LWPOLYLINE") (100 . "AcDbEntity") (8 . "PLANTS") (62 . 94) (370 . 13) (100 . "AcDbPolyline") (90 . 2) (70 . 0)
(43 . 0.0) (10 7711.1623303167 279.0356334842) (10 7737.556561086 316.742081448))
((0 . "LWPOLYLINE") (100 . "AcDbEntity") (8 . "PLANTS") (62 . 94) (370 . 13) (100 . "AcDbPolyline") (90 . 3) (70 . 0)
(43 . 0.0) (10 7731.9004524887 6774.1324660633) (10 7732.5819004525 6806.1777149321) (10 7714.9321266968
6817.4964932127))
((0 . "LWPOLYLINE") (100 . "AcDbEntity") (8 . "PLANTS") (62 . 94) (370 . 13) (100 . "AcDbPolyline") (90 . 2) (70 . 0)
(43 . 0.0) (10 7726.2443438914 252.6385746606) (10 7726.2443438914 241.3263574661))
((0 . "LWPOLYLINE") (100 . "AcDbEntity") (8 . "PLANTS") (62 . 94) (370 . 13) (100 . "AcDbPolyline") (90 . 3) (70 . 0)
(43 . 0.0) (10 7812.9722850679 316.742081448) (10 7786.5752262443 300.6091628959) (10 7726.2443438914 252.6385746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7726.2443438914 241.3263574661 0.0) (10 7760.0703186939 207.6629274945 0.0) (10 7824.6570915178
260.6167888157 0.0) (10 7847.2866268723 214.9899412314 0.0))
((0 . "LWPOLYLINE") (100 . "AcDbEntity") (8 . "PLANTS") (62 . 94) (370 . 13) (100 . "AcDbPolyline") (90 . 2) (70 . 0)
(43 . 0.0) (10 7731.9004524887 6774.1324660633) (10 7733.7867647059 6730.7692307692))
((0 . "LWPOLYLINE") (100 . "AcDbEntity") (8 . "PLANTS") (62 . 94) (370 . 13) (100 . "AcDbPolyline") (90 . 3) (70 . 0)
(43 . 0.0) (10 7731.9004524887 6774.1324660633) (10 7763.9507918552 6775.8697963801) (10 7782.8054298643
6768.4763574661))
((0 . "LWPOLYLINE") (100 . "AcDbEntity") (8 . "PLANTS") (62 . 94) (370 . 13) (100 . "AcDbPolyline") (90 . 2) (70 . 0)
(43 . 0.0) (10 7752.6385746606 6723.2274886878) (10 7733.7867647059 6730.7692307692))
((0 . "LWPOLYLINE") (100 . "AcDbEntity") (8 . "PLANTS") (62 . 94) (370 . 13) (100 . "AcDbPolyline") (90 . 2) (70 . 0)
(43 . 0.0) (10 7745.0989819005 471.3433257919) (10 7733.7867647059 448.7188914027))
((0 . "LWPOLYLINE") (100 . "AcDbEntity") (8 . "PLANTS") (62 . 94) (370 . 13) (100 . "AcDbPolyline") (90 . 3) (70 . 0)
(43 . 0.0) (10 7763.9507918552 316.742081448) (10 7756.4036199095 313.1255656109) (10 7737.556561086 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7801.6600678733 388.3851809955 0.0) (10 7789.060635135 357.3869644159 0.0) (10 7742.2855118007
352.6823842159 0.0) (10 7737.556561086 316.742081448 0.0))
((0 . "LWPOLYLINE") (100 . "AcDbEntity") (8 . "PLANTS") (62 . 94) (370 . 13) (100 . "AcDbPolyline") (90 . 2) (70 . 0)
(43 . 0.0) (10 7752.6385746606 6723.2274886878) (10 7756.411199095 6636.5010180995))
((0 . "LWPOLYLINE") (100 . "AcDbEntity") (8 . "PLANTS") (62 . 94) (370 . 13) (100 . "AcDbPolyline") (90 . 3) (70 . 0)
(43 . 0.0) (10 7752.6385746606 6723.2274886878) (10 7760.1878959276 6729.5714932127) (10 7779.0356334842
6734.5397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7777.0878529563 6587.4560335633 0.0) (10 7756.9360025223 6591.2305990906 0.0) (10 7754.9145157559
6620.0178949852 0.0) (10 7756.411199095 6636.5010180995 0.0))
((0 . "LWPOLYLINE") (100 . "AcDbEntity") (8 . "PLANTS") (62 . 94) (370 . 13) (100 . "AcDbPolyline") (90 . 3) (70 . 0)
(43 . 0.0) (10 7782.8971928778 6644.6556881749) (10 7775.2630090498 6637.5570135747) (10 7756.411199095
6636.5010180995))
((0 . "LWPOLYLINE") (100 . "AcDbEntity") (8 . "PLANTS") (62 . 94) (370 . 13) (100 . "AcDbPolyline") (90 . 3) (70 . 0)
(43 . 0.0) (10 7779.0356334842 6734.5397058824) (10 7786.5828054299 6730.9175339367) (10 7828.0542986425
6730.7692307692))
((0 . "LWPOLYLINE") (100 . "AcDbEntity") (8 . "PLANTS") (62 . 94) (370 . 13) (100 . "AcDbPolyline") (90 . 3) (70 . 0)
(43 . 0.0) (10 7782.8054298643 6768.4763574661) (10 7782.6576923077 6742.0880090498) (10 7779.0356334842
6734.5397058824))
((0 . "LWPOLYLINE") (100 . "AcDbEntity") (8 . "PLANTS") (62 . 94) (370 . 13) (100 . "AcDbPolyline") (90 . 3) (70 . 0)
(43 . 0.0) (10 7782.8054298643 6768.4763574661) (10 7797.8825791855 6769.6806561086) (10 7805.4298642534
6779.7885746606))
((0 . "LWPOLYLINE") (100 . "AcDbEntity") (8 . "PLANTS") (62 . 94) (370 . 13) (100 . "AcDbPolyline") (90 . 2) (70 . 0)
(43 . 0.0) (10 7797.8874434389 6802.4130090498) (10 7805.4298642534 6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7892.1578054299 6843.8914027149 0.0) (10 7871.7523588095 6817.3246651562 0.0) (10 7825.9103446884
6824.4130782891 0.0) (10 7801.6600678733 6843.8914027149 0.0))
((0 . "LWPOLYLINE") (100 . "AcDbEntity") (8 . "PLANTS") (62 . 94) (370 . 13) (100 . "AcDbPolyline") (90 . 3) (70 . 0)
(43 . 0.0) (10 7801.6600678733 6843.8914027149) (10 7814.0279411765 6874.0575791855) (10 7831.8240950226
6889.1402714932))
((0 . "LWPOLYLINE") (100 . "AcDbEntity") (8 . "PLANTS") (62 . 94) (370 . 13) (100 . "AcDbPolyline") (90 . 2) (70 . 0)
(43 . 0.0) (10 7805.4298642534 6779.7885746606) (10 7892.1578054299 6783.559841629))
((0 . "LWPOLYLINE") (100 . "AcDbEntity") (8 . "PLANTS") (62 . 94) (370 . 13) (100 . "AcDbPolyline") (90 . 3) (70 . 0)
(43 . 0.0) (10 7818.6283936652 6938.1596153846) (10 7817.7984162896 6911.7647058824) (10 7831.8240950226
6889.1402714932))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7818.6283936652 6938.1596153846 0.0) (10 7829.5579595891 6970.5701077323 0.0) (10 7834.8831292336
7007.8176884768 0.0) (10 7820.5118778281 7039.9695701357 0.0))
((0 . "LWPOLYLINE") (100 . "AcDbEntity") (8 . "PLANTS") (62 . 94) (370 . 13) (100 . "AcDbPolyline") (90 . 3) (70 . 0)
(43 . 0.0) (10 7818.6283936652 6938.1596153846) (10 7869.5333710407 6941.924321267) (10 7895.92760181 6938.1596153846))
((0 . "LWPOLYLINE") (100 . "AcDbEntity") (8 . "PLANTS") (62 . 94) (370 . 13) (100 . "AcDbPolyline") (90 . 2) (70 . 0)
(43 . 0.0) (10 7861.9909502262 6885.3697963801) (10 7831.8240950226 6889.1402714932))
((0 . "LWPOLYLINE") (100 . "AcDbEntity") (8 . "PLANTS") (62 . 94) (370 . 13) (100 . "AcDbPolyline") (90 . 2) (70 . 0)
(43 . 0.0) (10 7865.7607466063 6968.3257918552) (10 7854.4485294118 6964.5553167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7892.1578054299 6843.8914027149 0.0) (10 7890.4531098348 6864.226769038 0.0) (10 7864.2250819925
6865.8321419703 0.0) (10 7861.9909502262 6885.3697963801 0.0))
((0 . "LWPOLYLINE") (100 . "AcDbEntity") (8 . "PLANTS") (62 . 94) (370 . 13) (100 . "AcDbPolyline") (90 . 3) (70 . 0)
(43 . 0.0) (10 7861.9909502262 6885.3697963801) (10 7873.3031674208 6895.4842760181) (10 7899.69739819 6904.2229638009))
((0 . "LWPOLYLINE") (100 . "AcDbEntity") (8 . "PLANTS") (62 . 94) (370 . 13) (100 . "AcDbPolyline") (90 . 2) (70 . 0)
(43 . 0.0) (10 7888.3851809955 6806.1842760181) (10 7892.1578054299 6783.559841629))
((0 . "LWPOLYLINE") (100 . "AcDbEntity") (8 . "PLANTS") (62 . 94) (370 . 13) (100 . "AcDbPolyline") (90 . 3) (70 . 0)
(43 . 0.0) (10 7892.1578054299 6843.8914027149) (10 7944.9462669683 6844.0397058824) (10 7956.2584841629
6847.6618778281))
((0 . "LWPOLYLINE") (100 . "AcDbEntity") (8 . "PLANTS") (62 . 94) (370 . 13) (100 . "AcDbPolyline") (90 . 2) (70 . 0)
(43 . 0.0) (10 7918.5520361991 6776.0180995475) (10 7892.1578054299 6783.559841629))
((0 . "LWPOLYLINE") (100 . "AcDbEntity") (8 . "PLANTS") (62 . 94) (370 . 13) (100 . "AcDbPolyline") (90 . 2) (70 . 0)
(43 . 0.0) (10 7895.92760181 6938.1596153846) (10 7899.69739819 6919.3064479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7895.9276018099 6938.1596153846 0.0) (10 7904.5449694922 6965.9985090158 0.0) (10 7945.3800113077
6964.526545551 0.0) (10 7967.5707013574 6957.0135746607 0.0))
((0 . "LWPOLYLINE") (100 . "AcDbEntity") (8 . "PLANTS") (62 . 94) (370 . 13) (100 . "AcDbPolyline") (90 . 2) (70 . 0)
(43 . 0.0) (10 7941.1764705882 6919.3064479638) (10 7899.69739819 6919.3064479638))
((0 . "LWPOLYLINE") (100 . "AcDbEntity") (8 . "PLANTS") (62 . 94) (370 . 13) (100 . "AcDbPolyline") (90 . 2) (70 . 0)
(43 . 0.0) (10 7899.69739819 6904.2229638009) (10 7899.69739819 6919.3064479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 7899.69739819 6904.2229638009 0.0) (10 7944.2313317052 6912.6396645846 0.0) (10 7930.9679089519
6865.4249534767 0.0) (10 7956.2584841629 6855.2036199095 0.0))
((0 . "LWPOLYLINE") (100 . "AcDbEntity") (8 . "PLANTS") (62 . 94) (370 . 13) (100 . "AcDbPolyline") (90 . 2) (70 . 0)
(43 . 0.0) (10 7918.5520361991 6776.0180995475) (10 7922.3218325792 6757.1641402715))
((0 . "LWPOLYLINE") (100 . "AcDbEntity") (8 . "PLANTS") (62 . 94) (370 . 13) (100 . "AcDbPolyline") (90 . 3) (70 . 0)
(43 . 0.0) (10 7918.5520361991 6776.0180995475) (10 7975.1131221719 6787.0345022624) (10 8020.3619909502
6779.7885746606))
((0 . "LWPOLYLINE") (100 . "AcDbEntity") (8 . "PLANTS") (62 . 94) (370 . 13) (100 . "AcDbPolyline") (90 . 2) (70 . 0)
(43 . 0.0) (10 7956.2584841629 6847.6618778281) (10 7956.2584841629 6855.2036199095))
((0 . "LWPOLYLINE") (100 . "AcDbEntity") (8 . "PLANTS") (62 . 94) (370 . 13) (100 . "AcDbPolyline") (90 . 2) (70 . 0)
(43 . 0.0) (10 7975.1131221719 6862.745361991) (10 7956.2584841629 6855.2036199095))
((0 . "LWPOLYLINE") (100 . "AcDbEntity") (8 . "PLANTS") (62 . 94) (370 . 13) (100 . "AcDbPolyline") (90 . 3) (70 . 0)
(43 . 0.0) (10 7956.2584841629 6847.6618778281) (10 7975.1131221719 6836.4979638009) (10 8076.9230769231
6832.5791855204))
((0 . "LWPOLYLINE") (100 . "AcDbEntity") (8 . "PLANTS") (62 . 94) (370 . 13) (100 . "AcDbPolyline") (90 . 3) (70 . 0)
(43 . 0.0) (10 7993.967760181 6892.9107466063) (10 7978.882918552 6898.3466063348) (10 7967.5707013575 6896.6820135747))
((0 . "LWPOLYLINE") (100 . "AcDbEntity") (8 . "PLANTS") (62 . 94) (370 . 13) (100 . "AcDbPolyline") (90 . 3) (70 . 0)
(43 . 0.0) (10 7992.3918497024 6730.7692307692) (10 8012.6662895928 6742.0880090498) (10 8020.3619909502
6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 8076.9230769231 6832.5791855204 0.0) (10 8091.8263450263 6791.8203215365 0.0) (10 8049.9205428525
6770.3830805471 0.0) (10 8020.3619909502 6779.7885746606 0.0))
((0 . "LWPOLYLINE") (100 . "AcDbEntity") (8 . "PLANTS") (62 . 94) (370 . 13) (100 . "AcDbPolyline") (90 . 3) (70 . 0)
(43 . 0.0) (10 8076.9230769231 6832.5791855204) (10 8072.0961538462 6855.2036199095) (10 8058.068438914
6866.5158371041))
((0 . "LWPOLYLINE") (100 . "AcDbEntity") (8 . "PLANTS") (62 . 94) (370 . 13) (100 . "AcDbPolyline") (90 . 3) (70 . 0)
(43 . 0.0) (10 11949.4725113122 6892.9107466063) (10 11983.4091628959 6918.2496606335) (10 12021.1157239819
6923.0769230769))
((0 . "LWPOLYLINE") (100 . "AcDbEntity") (8 . "PLANTS") (62 . 94) (370 . 13) (100 . "AcDbPolyline") (90 . 3) (70 . 0)
(43 . 0.0) (10 12126.6968325792 6779.7885746606) (10 12107.8435520362 6783.553280543) (10 11968.3257918552
6783.559841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 11995.6228015426 6730.7692307692 0.0) (10 11970.9183997785 6735.1008221482 0.0) (10 11966.0714649954
6763.4059680511 0.0) (10 11968.3257918552 6783.559841629 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5770827039)
(40 . 0.9111231309) (40 . 1) (40 . 1) (40 . 1) (40 . 1) (10 12030.5429864253 6868.4014705882 0.0) (10 12010.8064023863
6826.3156429446 0.0) (10 11890.5930600547 6892.6686420541 0.0) (10 11925.2480437805 6772.3561732375 0.0) (10
11965.326709456 6786.5587574525 0.0) (10 11968.3257918552 6783.559841629 0.0))
((0 . "LWPOLYLINE") (100 . "AcDbEntity") (8 . "PLANTS") (62 . 94) (370 . 13) (100 . "AcDbPolyline") (90 . 3) (70 . 0)
(43 . 0.0) (10 12030.5429864253 6868.4014705882) (10 12013.5746606335 6884.165158371) (10 11994.7213800905
6885.3697963801))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.2928670761) (40
. 1) (40 . 1) (40 . 1) (40 . 1) (10 12030.5429864253 6868.4014705882 0.0) (10 12035.3441090083 6853.19571353 0.0) (10
12070.1893010916 6826.5035619453 0.0) (10 12130.9177186573 6854.0139052365 0.0) (10 12149.3212669683 6877.8280542986
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12030.5429864253 6868.4014705882 0.0) (10 12056.7266706184 6896.9431439287 0.0) (10 12107.6090569454
6887.5869255356 0.0) (10 12126.6968325792 6923.0769230769 0.0))
((0 . "LWPOLYLINE") (100 . "AcDbEntity") (8 . "PLANTS") (62 . 94) (370 . 13) (100 . "AcDbPolyline") (90 . 2) (70 . 0)
(43 . 0.0) (10 12077.6768099548 6923.0769230769) (10 12039.9702488688 6923.0769230769))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12187.0290723982 6738.3109728507 0.0) (10 12141.3465699808 6804.1254849367 0.0) (10 12095.2150866743
6715.8184286208 0.0) (10 12051.2824660634 6738.3109728507 0.0))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.2503858481)
(40 . 0.386495946) (40 . 0.7417692292) (40 . 1) (40 . 1) (40 . 1) (40 . 1) (10 12073.9069004525 6953.2430995475 0.0) (10
12057.2226861987 6949.2573237293 0.0) (10 12035.3291381731 6984.703039291 0.0) (10 12071.2216577651 7002.6081131327 0.0)
(10 12120.710346926 6963.927803542 0.0) (10 12148.7902062953 6999.2463296635 0.0) (10 12164.4046380091 6964.5553167421
0.0))
((0 . "LWPOLYLINE") (100 . "AcDbEntity") (8 . "PLANTS") (62 . 94) (370 . 13) (100 . "AcDbPolyline") (90 . 3) (70 . 0)
(43 . 0.0) (10 12126.6968325792 6923.0769230769) (10 12125.4926470588 6930.6252262443) (10 12115.3846153846
6941.9308823529))
((0 . "LWPOLYLINE") (100 . "AcDbEntity") (8 . "PLANTS") (62 . 94) (370 . 13) (100 . "AcDbPolyline") (90 . 2) (70 . 0)
(43 . 0.0) (10 12126.6968325792 6779.7885746606) (10 12122.925678733 6760.9354072398))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12190.7989819005 6938.1596153846 0.0) (10 12180.1394673619 6915.8487619245 0.0) (10 12146.9627745559
6911.5861444261 0.0) (10 12126.6968325792 6923.0769230769 0.0))
((0 . "LWPOLYLINE") (100 . "AcDbEntity") (8 . "PLANTS") (62 . 94) (370 . 13) (100 . "AcDbPolyline") (90 . 2) (70 . 0)
(43 . 0.0) (10 12145.5501131222 6783.559841629) (10 12126.6968325792 6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12141.0556983182 319.576971195 0.0) (10 12174.6087833036 319.4650320802 0.0) (10 12185.4719165406
278.5626298911 0.0) (10 12217.1945701357 275.2630090498 0.0))
((0 . "LWPOLYLINE") (100 . "AcDbEntity") (8 . "PLANTS") (62 . 94) (370 . 13) (100 . "AcDbPolyline") (90 . 2) (70 . 0)
(43 . 0.0) (10 12134.2378959276 6832.5791855204) (10 12141.7802036199 6828.8087104072))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12236.0478506787 245.0989819005 0.0) (10 12206.6726407891 215.310435531 0.0) (10 12160.3786262858
247.288750216 0.0) (10 12127.8988079537 226.2416728351 0.0))
((0 . "LWPOLYLINE") (100 . "AcDbEntity") (8 . "PLANTS") (62 . 94) (370 . 13) (100 . "AcDbPolyline") (90 . 2) (70 . 0)
(43 . 0.0) (10 12145.5501131222 6783.559841629) (10 12141.7802036199 6828.8087104072))
((0 . "LWPOLYLINE") (100 . "AcDbEntity") (8 . "PLANTS") (62 . 94) (370 . 13) (100 . "AcDbPolyline") (90 . 2) (70 . 0)
(43 . 0.0) (10 12190.7989819005 6840.1209276018) (10 12141.7802036199 6828.8087104072))
((0 . "LWPOLYLINE") (100 . "AcDbEntity") (8 . "PLANTS") (62 . 94) (370 . 13) (100 . "AcDbPolyline") (90 . 2) (70 . 0)
(43 . 0.0) (10 12145.5501131222 6783.559841629) (10 12247.3600678733 6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12236.0478506789 263.9507918551 0.0) (10 12268.474256142 320.934998807 0.0) (10 12194.6280707843
386.3725556571 0.0) (10 12156.3937161137 419.2740868653 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12217.1945701357 275.2630090498 0.0) (10 12234.1588967917 313.0709478981 0.0) (10 12166.6928792367
335.7053031612 0.0) (10 12164.4046380091 365.7607466063 0.0))
((0 . "LWPOLYLINE") (100 . "AcDbEntity") (8 . "PLANTS") (62 . 94) (370 . 13) (100 . "AcDbPolyline") (90 . 2) (70 . 0)
(43 . 0.0) (10 12187.0290723982 7068.2501131222) (10 12187.0289973976 7149.8132797754))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12285.0678733032 7013.5746606335 0.0) (10 12243.2609704778 7014.6881072502 0.0) (10 12232.1413791017
7074.3565794509 0.0) (10 12187.0290723982 7068.2501131222 0.0))
((0 . "LWPOLYLINE") (100 . "AcDbEntity") (8 . "PLANTS") (62 . 94) (370 . 13) (100 . "AcDbPolyline") (90 . 2) (70 . 0)
(43 . 0.0) (10 12187.0290723982 7068.2501131222) (10 12190.7989819005 7032.4286199095))
((0 . "SPLINE") (100 . "AcDbEntity") (8 . "PLANTS") (62 . 94) (370 . 13) (100 . "AcDbSpline") (70 . 0) (71 . 3) (72 .
13) (73 . 9) (74 . 0) (42 . 0.0000001) (43 . 0.0000001) (40 . 0.0) (40 . 0.0) (40 . 0.0) (40 . 0.0) (40 . 0.1287885393)
(40 . 0.2273637379) (40 . 0.361619251) (40 . 0.4944264258) (40 . 0.7628283906) (40 . 1) (40 . 1) (40 . 1) (40 . 1) (10
12224.7356334841 6941.9308823529 0.0) (10 12218.5196596677 6951.2059005218 0.0) (10 12214.9972640623 6967.8708987912
0.0) (10 12187.5252689083 6975.6335839299 0.0) (10 12175.5973076143 7003.4114520938 0.0) (10 12148.0479015081
7029.5912964727 0.0) (10 12102.8910014115 7091.683289588 0.0) (10 12187.7658937954 7084.7413225556 0.0) (10
12187.0290723982 7068.2501131222 0.0))
((0 . "LWPOLYLINE") (100 . "AcDbEntity") (8 . "PLANTS") (62 . 94) (370 . 13) (100 . "AcDbPolyline") (90 . 3) (70 . 0)
(43 . 0.0) (10 12187.0290723982 6960.7840497738) (10 12183.5548642534 6953.236199095) (10 12190.7989819005
6938.1596153846))
((0 . "LWPOLYLINE") (100 . "AcDbEntity") (8 . "PLANTS") (62 . 94) (370 . 13) (100 . "AcDbPolyline") (90 . 2) (70 . 0)
(43 . 0.0) (10 12217.1945701357 6934.3891402715) (10 12190.7989819005 6938.1596153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12190.7989819005 6840.1209276018 0.0) (10 12212.1949451785 6824.1325688228 0.0) (10 12253.5320783602
6831.9368183278 0.0) (10 12254.9023755656 6862.745361991 0.0))
((0 . "LWPOLYLINE") (100 . "AcDbEntity") (8 . "PLANTS") (62 . 94) (370 . 13) (100 . "AcDbPolyline") (90 . 3) (70 . 0)
(43 . 0.0) (10 12217.1945701357 6874.0575791855) (10 12198.496040724 6862.738800905) (10 12190.7989819005
6840.1209276018))
((0 . "LWPOLYLINE") (100 . "AcDbEntity") (8 . "PLANTS") (62 . 94) (370 . 13) (100 . "AcDbPolyline") (90 . 3) (70 . 0)
(43 . 0.0) (10 12209.6535067873 6738.3109728507) (10 12236.0478506787 6738.4588235294) (10 12254.9023755656
6745.8519230769))
((0 . "LWPOLYLINE") (100 . "AcDbEntity") (8 . "PLANTS") (62 . 94) (370 . 13) (100 . "AcDbPolyline") (90 . 2) (70 . 0)
(43 . 0.0) (10 12220.9657239819 6998.4919683258) (10 12217.1945701357 7009.8041855204))
((0 . "LWPOLYLINE") (100 . "AcDbEntity") (8 . "PLANTS") (62 . 94) (370 . 13) (100 . "AcDbPolyline") (90 . 2) (70 . 0)
(43 . 0.0) (10 12217.1945701357 6990.9502262443) (10 12220.9657239819 6998.4919683258))
((0 . "LWPOLYLINE") (100 . "AcDbEntity") (8 . "PLANTS") (62 . 94) (370 . 13) (100 . "AcDbPolyline") (90 . 2) (70 . 0)
(43 . 0.0) (10 12217.1945701357 6874.0575791855) (10 12217.1945701357 6934.3891402715))
((0 . "LWPOLYLINE") (100 . "AcDbEntity") (8 . "PLANTS") (62 . 94) (370 . 13) (100 . "AcDbPolyline") (90 . 2) (70 . 0)
(43 . 0.0) (10 12224.7356334842 6941.9308823529) (10 12217.1945701357 6934.3891402715))
((0 . "LWPOLYLINE") (100 . "AcDbEntity") (8 . "PLANTS") (62 . 94) (370 . 13) (100 . "AcDbPolyline") (90 . 3) (70 . 0)
(43 . 0.0) (10 12217.1945701357 6874.0575791855) (10 12247.3531674208 6869.088800905) (10 12254.9023755656
6862.745361991))
((0 . "LWPOLYLINE") (100 . "AcDbEntity") (8 . "PLANTS") (62 . 94) (370 . 13) (100 . "AcDbPolyline") (90 . 2) (70 . 0)
(43 . 0.0) (10 12217.1945701357 275.2630090498) (10 12236.0478506787 263.9507918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12220.9657239819 6998.4919683258 0.0) (10 12246.4182290968 6994.8789968923 0.0) (10 12266.1010116992
6967.0879239193 0.0) (10 12262.443438914 6941.9308823529 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7383055404) (40
. 1) (40 . 1) (40 . 1) (40 . 1) (10 12220.9657239819 471.3433257918 0.0) (10 12246.3665596726 432.9920966652 0.0) (10
12261.0148358477 370.5120645228 0.0) (10 12274.9758681286 311.0644962253 0.0) (10 12288.8390271492 301.6600678732 0.0))
((0 . "LWPOLYLINE") (100 . "AcDbEntity") (8 . "PLANTS") (62 . 94) (370 . 13) (100 . "AcDbPolyline") (90 . 3) (70 . 0)
(43 . 0.0) (10 12224.7356334842 6941.9308823529) (10 12247.3600678733 6941.7760180995) (10 12262.443438914
6934.3891402715))
((0 . "LWPOLYLINE") (100 . "AcDbEntity") (8 . "PLANTS") (62 . 94) (370 . 13) (100 . "AcDbPolyline") (90 . 2) (70 . 0)
(43 . 0.0) (10 12233.4837829813 6606.7907495488) (10 12239.8190045249 6613.8765837104))
((0 . "LWPOLYLINE") (100 . "AcDbEntity") (8 . "PLANTS") (62 . 94) (370 . 13) (100 . "AcDbPolyline") (90 . 2) (70 . 0)
(43 . 0.0) (10 12236.0478506787 263.9507918552) (10 12236.0478506787 245.0989819005))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12236.0478506787 245.0989819004 0.0) (10 12252.410899567 236.4283455002 0.0) (10 12275.7842723518
230.5783059582 0.0) (10 12292.6089366516 241.3263574661 0.0))
((0 . "LWPOLYLINE") (100 . "AcDbEntity") (8 . "PLANTS") (62 . 94) (370 . 13) (100 . "AcDbPolyline") (90 . 2) (70 . 0)
(43 . 0.0) (10 12243.7309595336 6514.5661605773) (10 12247.3600678733 6512.0662895928))
((0 . "LWPOLYLINE") (100 . "AcDbEntity") (8 . "PLANTS") (62 . 94) (370 . 13) (100 . "AcDbPolyline") (90 . 3) (70 . 0)
(43 . 0.0) (10 12254.9023755656 6745.8519230769) (10 12254.7477375566 6764.7058823529) (10 12247.3600678733
6779.7885746606))
((0 . "LWPOLYLINE") (100 . "AcDbEntity") (8 . "PLANTS") (62 . 94) (370 . 13) (100 . "AcDbPolyline") (90 . 2) (70 . 0)
(43 . 0.0) (10 12247.3600678733 6779.7885746606) (10 12258.6722850679 6783.559841629))
((0 . "LWPOLYLINE") (100 . "AcDbEntity") (8 . "PLANTS") (62 . 94) (370 . 13) (100 . "AcDbPolyline") (90 . 2) (70 . 0)
(43 . 0.0) (10 12247.3600678733 6512.0662895928) (10 12247.3600678733 6481.9041855204))
((0 . "LWPOLYLINE") (100 . "AcDbEntity") (8 . "PLANTS") (62 . 94) (370 . 13) (100 . "AcDbPolyline") (90 . 3) (70 . 0)
(43 . 0.0) (10 12273.7556561086 6546.003280543) (10 12257.6227375566 6519.614479638) (10 12247.3600678733
6512.0662895928))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12247.360482651 6481.9004525215 0.0) (10 12289.4776148472 6446.9888261273 0.0) (10 12331.0127192771
6499.6588845755 0.0) (10 12371.7944570136 6481.9004524887 0.0))
((0 . "LWPOLYLINE") (100 . "AcDbEntity") (8 . "PLANTS") (62 . 94) (370 . 13) (100 . "AcDbPolyline") (90 . 2) (70 . 0)
(43 . 0.0) (10 12251.1312217195 6557.3154977376) (10 12262.443438914 6561.0859728507))
((0 . "LWPOLYLINE") (100 . "AcDbEntity") (8 . "PLANTS") (62 . 94) (370 . 13) (100 . "AcDbPolyline") (90 . 3) (70 . 0)
(43 . 0.0) (10 12281.296719457 6877.8280542986) (10 12269.9845022624 6867.5718325792) (10 12254.9023755656
6862.745361991))
((0 . "LWPOLYLINE") (100 . "AcDbEntity") (8 . "PLANTS") (62 . 94) (370 . 13) (100 . "AcDbPolyline") (90 . 3) (70 . 0)
(43 . 0.0) (10 12288.8390271493 6738.3109728507) (10 12273.7556561086 6738.4588235294) (10 12254.9023755656
6745.8519230769))
((0 . "LWPOLYLINE") (100 . "AcDbEntity") (8 . "PLANTS") (62 . 94) (370 . 13) (100 . "AcDbPolyline") (90 . 2) (70 . 0)
(43 . 0.0) (10 12258.6722850679 6783.559841629) (10 12296.3800904977 6776.0180995475))
((0 . "LWPOLYLINE") (100 . "AcDbEntity") (8 . "PLANTS") (62 . 94) (370 . 13) (100 . "AcDbPolyline") (90 . 2) (70 . 0)
(43 . 0.0) (10 12262.443438914 6794.8720588235) (10 12258.6722850679 6783.559841629))
((0 . "LWPOLYLINE") (100 . "AcDbEntity") (8 . "PLANTS") (62 . 94) (370 . 13) (100 . "AcDbPolyline") (90 . 2) (70 . 0)
(43 . 0.0) (10 12321.086122851 863.4949313619) (10 12327.3879586849 863.4956335637))
((0 . "LWPOLYLINE") (100 . "AcDbEntity") (8 . "PLANTS") (62 . 94) (370 . 13) (100 . "AcDbPolyline") (90 . 3) (70 . 0)
(43 . 0.0) (10 12262.443438914 6941.9308823529) (10 12315.2333710407 6933.1914027149) (10 12330.3167420814
6919.3064479638))
((0 . "LWPOLYLINE") (100 . "AcDbEntity") (8 . "PLANTS") (62 . 94) (370 . 13) (100 . "AcDbPolyline") (90 . 2) (70 . 0)
(43 . 0.0) (10 12262.443438914 6934.3891402715) (10 12262.443438914 6941.9308823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12281.296719457 6877.8280542986 0.0) (10 12260.5652427071 6891.6270590208 0.0) (10 12278.054656955
6917.5563032738 0.0) (10 12262.443438914 6934.3891402715 0.0))
((0 . "LWPOLYLINE") (100 . "AcDbEntity") (8 . "PLANTS") (62 . 94) (370 . 13) (100 . "AcDbPolyline") (90 . 2) (70 . 0)
(43 . 0.0) (10 12262.443438914 6561.0859728507) (10 12273.7556561086 6546.003280543))
((0 . "LWPOLYLINE") (100 . "AcDbEntity") (8 . "PLANTS") (62 . 94) (370 . 13) (100 . "AcDbPolyline") (90 . 2) (70 . 0)
(43 . 0.0) (10 12262.443438914 6561.0859728507) (10 12277.5268099548 6576.1686651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12269.9845022624 6659.1254524887 0.0) (10 12260.0219702973 6671.9547475875 0.0) (10 12273.9186144977
6693.5665668962 0.0) (10 12288.8390271493 6693.0621040724 0.0))
((0 . "LWPOLYLINE") (100 . "AcDbEntity") (8 . "PLANTS") (62 . 94) (370 . 13) (100 . "AcDbPolyline") (90 . 2) (70 . 0)
(43 . 0.0) (10 12281.296719457 6610.1053167421) (10 12269.9845022624 6613.8765837104))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12273.7556561086 6546.003280543 0.0) (10 12285.7728854672 6549.4284030012 0.0) (10 12296.0024676167
6570.7366892494 0.0) (10 12277.5268099548 6576.1686651584 0.0))
((0 . "LWPOLYLINE") (100 . "AcDbEntity") (8 . "PLANTS") (62 . 94) (370 . 13) (100 . "AcDbPolyline") (90 . 2) (70 . 0)
(43 . 0.0) (10 12281.296719457 6610.1053167421) (10 12277.5268099548 6576.1686651584))
((0 . "LWPOLYLINE") (100 . "AcDbEntity") (8 . "PLANTS") (62 . 94) (370 . 13) (100 . "AcDbPolyline") (90 . 3) (70 . 0)
(43 . 0.0) (10 12281.296719457 6877.8280542986) (10 12288.8459276018 6881.450678733) (10 12311.4634615385
6881.5985294118))
((0 . "LWPOLYLINE") (100 . "AcDbEntity") (8 . "PLANTS") (62 . 94) (370 . 13) (100 . "AcDbPolyline") (90 . 3) (70 . 0)
(43 . 0.0) (10 12281.296719457 6640.2714932127) (10 12292.6033936652 6643.7461538462) (10 12300.1512443439
6640.2714932127))
((0 . "LWPOLYLINE") (100 . "AcDbEntity") (8 . "PLANTS") (62 . 94) (370 . 13) (100 . "AcDbPolyline") (90 . 3) (70 . 0)
(43 . 0.0) (10 12281.296719457 6610.1053167421) (10 12298.9471719457 6617.795361991) (10 12300.1512443439
6640.2714932127))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5446472348) (40
. 1) (40 . 1) (40 . 1) (40 . 1) (10 12285.0678733031 7013.5746606333 0.0) (10 12298.7323821861 7002.1338582251 0.0) (10
12343.1130075682 6978.4590492239 0.0) (10 12354.467937064 6938.218910297 0.0) (10 12341.628959276 6919.3064479637 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2654020691)
(40 . 0.4264332584) (40 . 1) (40 . 1) (40 . 1) (40 . 1) (10 12285.0678733032 7013.5746606334 0.0) (10 12282.4103749517
7036.1693279183 0.0) (10 12308.7872889501 7063.8958445376 0.0) (10 12376.0702985564 7035.0853401234 0.0) (10
12359.5733292966 6954.2685724096 0.0) (10 12401.961199095 6941.930882353 0.0))
((0 . "LWPOLYLINE") (100 . "AcDbEntity") (8 . "PLANTS") (62 . 94) (370 . 13) (100 . "AcDbPolyline") (90 . 3) (70 . 0)
(43 . 0.0) (10 12412.9311252894 786.5067836196) (10 12401.961199095 784.3196832579) (10 12342.3982399759
786.2385067841))
((0 . "LWPOLYLINE") (100 . "AcDbEntity") (8 . "PLANTS") (62 . 94) (370 . 13) (100 . "AcDbPolyline") (90 . 2) (70 . 0)
(43 . 0.0) (10 12288.8390271493 6738.3109728507) (10 12296.3800904977 6738.3109728507))
((0 . "LWPOLYLINE") (100 . "AcDbEntity") (8 . "PLANTS") (62 . 94) (370 . 13) (100 . "AcDbPolyline") (90 . 2) (70 . 0)
(43 . 0.0) (10 12288.8390271493 6738.3109728507) (10 12288.8390271493 6693.0621040724))
((0 . "LWPOLYLINE") (100 . "AcDbEntity") (8 . "PLANTS") (62 . 94) (370 . 13) (100 . "AcDbPolyline") (90 . 2) (70 . 0)
(43 . 0.0) (10 12288.8390271493 6693.0621040724) (10 12303.9211538462 6681.7498868778))
((0 . "LWPOLYLINE") (100 . "AcDbEntity") (8 . "PLANTS") (62 . 94) (370 . 13) (100 . "AcDbPolyline") (90 . 2) (70 . 0)
(43 . 0.0) (10 12288.8390271493 301.6600678733) (10 12292.6089366516 241.3263574661))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12311.4634615385 335.596719457 0.0) (10 12313.8266232056 320.3730659436 0.0) (10 12299.8953728352
308.8647385303 0.0) (10 12288.8390271493 301.6600678733 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12379.3367647059 256.411199095 0.0) (10 12364.2137194579 223.6601529475 0.0) (10 12319.6083622109
230.7299266077 0.0) (10 12292.6089366516 241.3263574661 0.0))
((0 . "LWPOLYLINE") (100 . "AcDbEntity") (8 . "PLANTS") (62 . 94) (370 . 13) (100 . "AcDbPolyline") (90 . 2) (70 . 0)
(43 . 0.0) (10 12311.4634615385 6776.0180995475) (10 12296.3800904977 6776.0180995475))
((0 . "LWPOLYLINE") (100 . "AcDbEntity") (8 . "PLANTS") (62 . 94) (370 . 13) (100 . "AcDbPolyline") (90 . 2) (70 . 0)
(43 . 0.0) (10 12296.3800904977 6738.3109728507) (10 12296.3800904977 6776.0180995475))
((0 . "LWPOLYLINE") (100 . "AcDbEntity") (8 . "PLANTS") (62 . 94) (370 . 13) (100 . "AcDbPolyline") (90 . 2) (70 . 0)
(43 . 0.0) (10 12322.775678733 6738.3109728507) (10 12296.3800904977 6738.3109728507))
((0 . "LWPOLYLINE") (100 . "AcDbEntity") (8 . "PLANTS") (62 . 94) (370 . 13) (100 . "AcDbPolyline") (90 . 3) (70 . 0)
(43 . 0.0) (10 12300.1512443439 6640.2714932127) (10 12319.0045248869 6647.6649321267) (10 12352.9411764706
6644.0419683258))
((0 . "LWPOLYLINE") (100 . "AcDbEntity") (8 . "PLANTS") (62 . 94) (370 . 13) (100 . "AcDbPolyline") (90 . 3) (70 . 0)
(43 . 0.0) (10 12356.7123303167 6847.6618778281) (10 12334.093438914 6855.3584841629) (10 12311.4634615385
6881.5985294118))
((0 . "LWPOLYLINE") (100 . "AcDbEntity") (8 . "PLANTS") (62 . 94) (370 . 13) (100 . "AcDbPolyline") (90 . 2) (70 . 0)
(43 . 0.0) (10 12311.4634615385 6881.5985294118) (10 12330.3167420814 6919.3064479638))
((0 . "LWPOLYLINE") (100 . "AcDbEntity") (8 . "PLANTS") (62 . 94) (370 . 13) (100 . "AcDbPolyline") (90 . 2) (70 . 0)
(43 . 0.0) (10 12322.775678733 6772.2476244344) (10 12311.4634615385 6776.0180995475))
((0 . "LWPOLYLINE") (100 . "AcDbEntity") (8 . "PLANTS") (62 . 94) (370 . 13) (100 . "AcDbPolyline") (90 . 3) (70 . 0)
(43 . 0.0) (10 12330.3167420814 6817.4964932127) (10 12316.4319004525 6806.1839366516) (10 12311.4634615385
6776.0180995475))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5377805516) (40
. 1) (40 . 1) (40 . 1) (40 . 1) (10 12322.775678733 456.258484163 0.0) (10 12295.6209286697 449.9901475313 0.0) (10
12284.7586565113 399.4917723791 0.0) (10 12298.8999091194 349.9247898596 0.0) (10 12311.4634615384 335.596719457 0.0))
((0 . "LWPOLYLINE") (100 . "AcDbEntity") (8 . "PLANTS") (62 . 94) (370 . 13) (100 . "AcDbPolyline") (90 . 3) (70 . 0)
(43 . 0.0) (10 12337.8578054299 361.9909502262) (10 12326.3977375566 343.2847285068) (10 12311.4634615385
335.596719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12315.2333710407 7115.3846153846 0.0) (10 12333.5153971872 7129.7896112776 0.0) (10 12359.2405362927
7099.6034628964 0.0) (10 12352.9411764706 7081.4479638009 0.0))
((0 . "LWPOLYLINE") (100 . "AcDbEntity") (8 . "PLANTS") (62 . 94) (370 . 13) (100 . "AcDbPolyline") (90 . 3) (70 . 0)
(43 . 0.0) (10 12322.775678733 6772.2476244344) (10 12360.482239819 6772.099321267) (10 12375.5656108597
6764.7058823529))
((0 . "LWPOLYLINE") (100 . "AcDbEntity") (8 . "PLANTS") (62 . 94) (370 . 13) (100 . "AcDbPolyline") (90 . 2) (70 . 0)
(43 . 0.0) (10 12322.775678733 6738.3109728507) (10 12322.775678733 6772.2476244344))
((0 . "LWPOLYLINE") (100 . "AcDbEntity") (8 . "PLANTS") (62 . 94) (370 . 13) (100 . "AcDbPolyline") (90 . 2) (70 . 0)
(43 . 0.0) (10 12322.775678733 6738.3109728507) (10 12345.4001131222 6715.6865384615))
((0 . "LWPOLYLINE") (100 . "AcDbEntity") (8 . "PLANTS") (62 . 94) (370 . 13) (100 . "AcDbPolyline") (90 . 2) (70 . 0)
(43 . 0.0) (10 12334.0878959276 6436.6515837104) (10 12322.775678733 6432.8807692308))
((0 . "LWPOLYLINE") (100 . "AcDbEntity") (8 . "PLANTS") (62 . 94) (370 . 13) (100 . "AcDbPolyline") (90 . 3) (70 . 0)
(43 . 0.0) (10 12322.775678733 456.2584841629) (10 12326.5455882353 471.3433257919) (10 12322.775678733 497.7375565611))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12322.775678733 456.2584841629 0.0) (10 12349.9970031054 444.0469349916 0.0) (10 12365.4747160215
413.1838700317 0.0) (10 12360.482239819 384.6153846154 0.0))
((0 . "LWPOLYLINE") (100 . "AcDbEntity") (8 . "PLANTS") (62 . 94) (370 . 13) (100 . "AcDbPolyline") (90 . 2) (70 . 0)
(43 . 0.0) (10 12341.628959276 6919.3064479638) (10 12330.3167420814 6919.3064479638))
((0 . "LWPOLYLINE") (100 . "AcDbEntity") (8 . "PLANTS") (62 . 94) (370 . 13) (100 . "AcDbPolyline") (90 . 2) (70 . 0)
(43 . 0.0) (10 12345.4001131222 6715.6865384615) (10 12330.3167420814 6689.2908371041))
((0 . "LWPOLYLINE") (100 . "AcDbEntity") (8 . "PLANTS") (62 . 94) (370 . 13) (100 . "AcDbPolyline") (90 . 2) (70 . 0)
(43 . 0.0) (10 12334.0878959276 6583.7104072398) (10 12334.0878959276 6591.2521493213))
((0 . "LWPOLYLINE") (100 . "AcDbEntity") (8 . "PLANTS") (62 . 94) (370 . 13) (100 . "AcDbPolyline") (90 . 2) (70 . 0)
(43 . 0.0) (10 12334.0878959276 6583.7104072398) (10 12337.8578054299 6576.1686651584))
((0 . "LWPOLYLINE") (100 . "AcDbEntity") (8 . "PLANTS") (62 . 94) (370 . 13) (100 . "AcDbPolyline") (90 . 2) (70 . 0)
(43 . 0.0) (10 12368.0245475113 6587.4808823529) (10 12334.0878959276 6583.7104072398))
((0 . "LWPOLYLINE") (100 . "AcDbEntity") (8 . "PLANTS") (62 . 94) (370 . 13) (100 . "AcDbPolyline") (90 . 2) (70 . 0)
(43 . 0.0) (10 12341.628959276 6432.8807692308) (10 12334.0878959276 6436.6515837104))
((0 . "LWPOLYLINE") (100 . "AcDbEntity") (8 . "PLANTS") (62 . 94) (370 . 13) (100 . "AcDbPolyline") (90 . 2) (70 . 0)
(43 . 0.0) (10 12337.8578054299 6447.963800905) (10 12334.0878959276 6436.6515837104))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12345.4001131222 6334.8416289593 0.0) (10 12335.3417363486 6325.0488614627 0.0) (10 12324.7066208164
6307.3129819881 0.0) (10 12334.0878959276 6293.3635746606 0.0))
((0 . "LWPOLYLINE") (100 . "AcDbEntity") (8 . "PLANTS") (62 . 94) (370 . 13) (100 . "AcDbPolyline") (90 . 2) (70 . 0)
(43 . 0.0) (10 12337.8578054299 361.9909502262) (10 12334.0878959276 380.8455882353))
((0 . "LWPOLYLINE") (100 . "AcDbEntity") (8 . "PLANTS") (62 . 94) (370 . 13) (100 . "AcDbPolyline") (90 . 3) (70 . 0)
(43 . 0.0) (10 12364.2533936652 6530.9197963801) (10 12345.4070135747 6529.7222850679) (10 12337.8578054299
6523.3788461538))
((0 . "LWPOLYLINE") (100 . "AcDbEntity") (8 . "PLANTS") (62 . 94) (370 . 13) (100 . "AcDbPolyline") (90 . 2) (70 . 0)
(43 . 0.0) (10 12337.8578054299 361.9909502262) (10 12356.7123303167 361.9909502262))
((0 . "LWPOLYLINE") (100 . "AcDbEntity") (8 . "PLANTS") (62 . 94) (370 . 13) (100 . "AcDbPolyline") (90 . 2) (70 . 0)
(43 . 0.0) (10 12341.628959276 6919.3064479638) (10 12379.3367647059 6911.7647058824))
((0 . "LWPOLYLINE") (100 . "AcDbEntity") (8 . "PLANTS") (62 . 94) (370 . 13) (100 . "AcDbPolyline") (90 . 3) (70 . 0)
(43 . 0.0) (10 12356.7123303167 6847.6618778281) (10 12351.884841629 6825.1923076923) (10 12341.628959276
6821.2669683258))
((0 . "LWPOLYLINE") (100 . "AcDbEntity") (8 . "PLANTS") (62 . 94) (370 . 13) (100 . "AcDbPolyline") (90 . 2) (70 . 0)
(43 . 0.0) (10 12371.7944570136 6715.6865384615) (10 12345.4001131222 6715.6865384615))
((0 . "LWPOLYLINE") (100 . "AcDbEntity") (8 . "PLANTS") (62 . 94) (370 . 13) (100 . "AcDbPolyline") (90 . 3) (70 . 0)
(43 . 0.0) (10 12371.7944570136 6625.188800905) (10 12356.867081448 6632.8780542986) (10 12352.9411764706
6644.0419683258))
((0 . "LWPOLYLINE") (100 . "AcDbEntity") (8 . "PLANTS") (62 . 94) (370 . 13) (100 . "AcDbPolyline") (90 . 3) (70 . 0)
(43 . 0.0) (10 12371.7944570136 6655.3541855204) (10 12364.2464932127 6654.1498868778) (10 12352.9411764706
6644.0419683258))
((0 . "LWPOLYLINE") (100 . "AcDbEntity") (8 . "PLANTS") (62 . 94) (370 . 13) (100 . "AcDbPolyline") (90 . 2) (70 . 0)
(43 . 0.0) (10 12356.7123303167 6847.6618778281) (10 12383.1066742081 6851.4331447964))
((0 . "LWPOLYLINE") (100 . "AcDbEntity") (8 . "PLANTS") (62 . 94) (370 . 13) (100 . "AcDbPolyline") (90 . 2) (70 . 0)
(43 . 0.0) (10 12356.7123303167 361.9909502262) (10 12364.2533936652 339.3665158371))
((0 . "LWPOLYLINE") (100 . "AcDbEntity") (8 . "PLANTS") (62 . 94) (370 . 13) (100 . "AcDbPolyline") (90 . 2) (70 . 0)
(43 . 0.0) (10 12360.482239819 384.6153846154) (10 12356.7123303167 361.9909502262))
((0 . "LWPOLYLINE") (100 . "AcDbEntity") (8 . "PLANTS") (62 . 94) (370 . 13) (100 . "AcDbPolyline") (90 . 2) (70 . 0)
(43 . 0.0) (10 12360.482239819 384.6153846154) (10 12383.1066742081 384.6153846154))
((0 . "LWPOLYLINE") (100 . "AcDbEntity") (8 . "PLANTS") (62 . 94) (370 . 13) (100 . "AcDbPolyline") (90 . 2) (70 . 0)
(43 . 0.0) (10 12364.2533936652 6530.9197963801) (10 12375.5656108597 6512.0662895928))
((0 . "LWPOLYLINE") (100 . "AcDbEntity") (8 . "PLANTS") (62 . 94) (370 . 13) (100 . "AcDbPolyline") (90 . 3) (70 . 0)
(43 . 0.0) (10 12375.5656108597 6579.9399321267) (10 12364.4080316742 6546.003280543) (10 12364.2533936652
6530.9197963801))
((0 . "LWPOLYLINE") (100 . "AcDbEntity") (8 . "PLANTS") (62 . 94) (370 . 13) (100 . "AcDbPolyline") (90 . 3) (70 . 0)
(43 . 0.0) (10 12371.7944570136 297.8874434389) (10 12364.4011312217 312.9722850679) (10 12364.2533936652
339.3665158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12383.1066742081 384.6153846154 0.0) (10 12401.6935094554 366.5830751731 0.0) (10 12382.0658796069
343.6554256711 0.0) (10 12364.2533936652 339.3665158371 0.0))
((0 . "LWPOLYLINE") (100 . "AcDbEntity") (8 . "PLANTS") (62 . 94) (370 . 13) (100 . "AcDbPolyline") (90 . 2) (70 . 0)
(43 . 0.0) (10 12368.0245475113 6587.4808823529) (10 12375.5656108597 6579.9399321267))
((0 . "LWPOLYLINE") (100 . "AcDbEntity") (8 . "PLANTS") (62 . 94) (370 . 13) (100 . "AcDbPolyline") (90 . 2) (70 . 0)
(43 . 0.0) (10 12368.0245475113 6587.4808823529) (10 12371.7944570136 6625.188800905))
((0 . "LWPOLYLINE") (100 . "AcDbEntity") (8 . "PLANTS") (62 . 94) (370 . 13) (100 . "AcDbPolyline") (90 . 2) (70 . 0)
(43 . 0.0) (10 12371.7944570136 6655.3541855204) (10 12371.7944570136 6715.6865384615))
((0 . "LWPOLYLINE") (100 . "AcDbEntity") (8 . "PLANTS") (62 . 94) (370 . 13) (100 . "AcDbPolyline") (90 . 2) (70 . 0)
(43 . 0.0) (10 12371.7944570136 6715.6865384615) (10 12383.1066742081 6719.4570135747))
((0 . "LWPOLYLINE") (100 . "AcDbEntity") (8 . "PLANTS") (62 . 94) (370 . 13) (100 . "AcDbPolyline") (90 . 3) (70 . 0)
(43 . 0.0) (10 12371.7944570136 6655.3541855204) (10 12382.9519230769 6651.4288461538) (10 12386.8778280543
6636.5010180995))
((0 . "LWPOLYLINE") (100 . "AcDbEntity") (8 . "PLANTS") (62 . 94) (370 . 13) (100 . "AcDbPolyline") (90 . 2) (70 . 0)
(43 . 0.0) (10 12371.7944570136 6625.188800905) (10 12386.8778280543 6636.5010180995))
((0 . "LWPOLYLINE") (100 . "AcDbEntity") (8 . "PLANTS") (62 . 94) (370 . 13) (100 . "AcDbPolyline") (90 . 2) (70 . 0)
(43 . 0.0) (10 12379.3367647059 6478.129638009) (10 12371.7944570136 6481.9004524887))
((0 . "LWPOLYLINE") (100 . "AcDbEntity") (8 . "PLANTS") (62 . 94) (370 . 13) (100 . "AcDbPolyline") (90 . 2) (70 . 0)
(43 . 0.0) (10 12371.7944570136 6481.9004524887) (10 12375.5656108597 6512.0662895928))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.5326410425)
(40 . 0.6337096652) (40 . 0.8172403446) (40 . 1) (40 . 1) (40 . 1) (40 . 1) (10 12375.5656108597 6406.4857466063 0.0)
(10 12368.9686272807 6366.8129637719 0.0) (10 12370.2872541131 6317.6231139016 0.0) (10 12374.9348250434 6257.2678813345
0.0) (10 12369.2545806575 6221.7290649053 0.0) (10 12382.1792270356 6193.2856762939 0.0) (10 12371.7944570137
6184.0119909502 0.0))
((0 . "LWPOLYLINE") (100 . "AcDbEntity") (8 . "PLANTS") (62 . 94) (370 . 13) (100 . "AcDbPolyline") (90 . 2) (70 . 0)
(43 . 0.0) (10 12379.3367647059 256.411199095) (10 12371.7944570136 297.8874434389))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4467789232)
(40 . 0.6960555361) (40 . 1) (40 . 1) (40 . 1) (40 . 1) (10 12371.7944570136 297.8874434389 0.0) (10 12391.2447788138
305.7613789821 0.0) (10 12404.1428934114 335.4429461602 0.0) (10 12446.1104639783 352.1430290941 0.0) (10
12463.552488967 367.5100202807 0.0) (10 12462.2921945701 384.6153846154 0.0))
((0 . "LWPOLYLINE") (100 . "AcDbEntity") (8 . "PLANTS") (62 . 94) (370 . 13) (100 . "AcDbPolyline") (90 . 3) (70 . 0)
(43 . 0.0) (10 12386.8778280543 6734.5397058824) (10 12376.7697963801 6742.0880090498) (10 12375.5656108597
6764.7058823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12375.5656108597 6764.7058823529 0.0) (10 12385.7847358442 6790.9911480794 0.0) (10 12394.7969309209
6823.8404080717 0.0) (10 12383.1066742081 6851.4331447964 0.0))
((0 . "LWPOLYLINE") (100 . "AcDbEntity") (8 . "PLANTS") (62 . 94) (370 . 13) (100 . "AcDbPolyline") (90 . 2) (70 . 0)
(43 . 0.0) (10 12405.7311085973 6583.7104072398) (10 12375.5656108597 6579.9399321267))
((0 . "LWPOLYLINE") (100 . "AcDbEntity") (8 . "PLANTS") (62 . 94) (370 . 13) (100 . "AcDbPolyline") (90 . 3) (70 . 0)
(43 . 0.0) (10 12390.6489819005 6515.8371040724) (10 12379.3367647059 6515.8371040724) (10 12375.5656108597
6512.0662895928))
((0 . "LWPOLYLINE") (100 . "AcDbEntity") (8 . "PLANTS") (62 . 94) (370 . 13) (100 . "AcDbPolyline") (90 . 2) (70 . 0)
(43 . 0.0) (10 12386.8778280543 6858.9740950226) (10 12379.3367647059 6911.7647058824))
((0 . "LWPOLYLINE") (100 . "AcDbEntity") (8 . "PLANTS") (62 . 94) (370 . 13) (100 . "AcDbPolyline") (90 . 2) (70 . 0)
(43 . 0.0) (10 12379.3367647059 6911.7647058824) (10 12401.961199095 6926.84739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12379.3367647059 6478.129638009 0.0) (10 12376.946863764 6457.5477834038 0.0) (10 12379.5099821473
6423.199331665 0.0) (10 12413.2734162896 6429.1101809955 0.0))
((0 . "LWPOLYLINE") (100 . "AcDbEntity") (8 . "PLANTS") (62 . 94) (370 . 13) (100 . "AcDbPolyline") (90 . 3) (70 . 0)
(43 . 0.0) (10 12379.3367647059 6478.129638009) (10 12405.7242081448 6478.2777149321) (10 12413.2734162896
6481.9004524887))
((0 . "LWPOLYLINE") (100 . "AcDbEntity") (8 . "PLANTS") (62 . 94) (370 . 13) (100 . "AcDbPolyline") (90 . 2) (70 . 0)
(43 . 0.0) (10 12386.8778280543 686.2754524887) (10 12379.3367647059 686.2754524887))
((0 . "LWPOLYLINE") (100 . "AcDbEntity") (8 . "PLANTS") (62 . 94) (370 . 13) (100 . "AcDbPolyline") (90 . 2) (70 . 0)
(43 . 0.0) (10 12379.3367647059 256.411199095) (10 12390.6489819005 256.411199095))
((0 . "LWPOLYLINE") (100 . "AcDbEntity") (8 . "PLANTS") (62 . 94) (370 . 13) (100 . "AcDbPolyline") (90 . 2) (70 . 0)
(43 . 0.0) (10 12386.8778280543 6858.9740950226) (10 12383.1066742081 6851.4331447964))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12445.3238687783 6630.8449095023 0.0) (10 12410.248516503 6651.0413859642 0.0) (10 12421.2317251417
6701.284512062 0.0) (10 12383.1066742081 6719.4570135747 0.0))
((0 . "LWPOLYLINE") (100 . "AcDbEntity") (8 . "PLANTS") (62 . 94) (370 . 13) (100 . "AcDbPolyline") (90 . 3) (70 . 0)
(43 . 0.0) (10 12386.8778280543 6734.5397058824) (10 12386.8778280543 6723.2274886878) (10 12383.1066742081
6719.4570135747))
((0 . "LWPOLYLINE") (100 . "AcDbEntity") (8 . "PLANTS") (62 . 94) (370 . 13) (100 . "AcDbPolyline") (90 . 2) (70 . 0)
(43 . 0.0) (10 12398.1900452489 399.69739819) (10 12383.1066742081 384.6153846154))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12439.667760181 6840.1209276018 0.0) (10 12431.0373670889 6857.2121163336 0.0) (10 12404.8508883207
6865.8196321196 0.0) (10 12386.8778280543 6858.9740950226 0.0))
((0 . "LWPOLYLINE") (100 . "AcDbEntity") (8 . "PLANTS") (62 . 94) (370 . 13) (100 . "AcDbPolyline") (90 . 3) (70 . 0)
(43 . 0.0) (10 12386.8778280543 6734.5397058824) (10 12409.3545248869 6753.3936651584) (10 12424.5856334842
6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12445.3238687783 6630.8449095023 0.0) (10 12424.5977655245 6621.0714859317 0.0) (10 12408.8909842428
6649.4675688176 0.0) (10 12386.8778280543 6636.5010180995 0.0))
((0 . "LWPOLYLINE") (100 . "AcDbEntity") (8 . "PLANTS") (62 . 94) (370 . 13) (100 . "AcDbPolyline") (90 . 3) (70 . 0)
(43 . 0.0) (10 12390.6489819005 6515.8371040724) (10 12390.5012443439 6542.2254524887) (10 12386.8778280543
6549.7737556561))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4338769704)
(40 . 0.5682961095) (40 . 1) (40 . 1) (40 . 1) (40 . 1) (10 12386.8778280543 686.2754524887 0.0) (10 12423.9511442443
690.723412544 0.0) (10 12460.257356377 655.2412698719 0.0) (10 12532.3110415307 615.6453387309 0.0) (10 12562.9113230555
580.4876201793 0.0) (10 12582.9566742081 550.5288461538 0.0))
((0 . "LWPOLYLINE") (100 . "AcDbEntity") (8 . "PLANTS") (62 . 94) (370 . 13) (100 . "AcDbPolyline") (90 . 3) (70 . 0)
(43 . 0.0) (10 12386.8778280543 686.2754524887) (10 12391.6985294118 659.8783936652) (10 12405.7311085973
633.4841628959))
((0 . "LWPOLYLINE") (100 . "AcDbEntity") (8 . "PLANTS") (62 . 94) (370 . 13) (100 . "AcDbPolyline") (90 . 2) (70 . 0)
(43 . 0.0) (10 12409.5022624434 6512.0662895928) (10 12390.6489819005 6515.8371040724))
((0 . "LWPOLYLINE") (100 . "AcDbEntity") (8 . "PLANTS") (62 . 94) (370 . 13) (100 . "AcDbPolyline") (90 . 2) (70 . 0)
(43 . 0.0) (10 12390.6489819005 456.2584841629) (10 12401.961199095 444.9462669683))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12469.8345022625 252.6385746606 0.0) (10 12449.3626354652 236.3821366614 0.0) (10 12404.0187132031
225.1368106217 0.0) (10 12390.6489819004 256.411199095 0.0))
((0 . "LWPOLYLINE") (100 . "AcDbEntity") (8 . "PLANTS") (62 . 94) (370 . 13) (100 . "AcDbPolyline") (90 . 3) (70 . 0)
(43 . 0.0) (10 12413.2734162896 286.5752262443) (10 12409.3476244344 275.2630090498) (10 12390.6489819005
256.411199095))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12398.1900452489 399.69739819 0.0) (10 12418.9963581657 380.0357718285 0.0) (10 12442.7473655861
413.1603424535 0.0) (10 12462.2921945701 384.6153846154 0.0))
((0 . "LWPOLYLINE") (100 . "AcDbEntity") (8 . "PLANTS") (62 . 94) (370 . 13) (100 . "AcDbPolyline") (90 . 2) (70 . 0)
(43 . 0.0) (10 12398.1900452489 399.69739819) (10 12401.961199095 444.9462669683))
((0 . "LWPOLYLINE") (100 . "AcDbEntity") (8 . "PLANTS") (62 . 94) (370 . 13) (100 . "AcDbPolyline") (90 . 2) (70 . 0)
(43 . 0.0) (10 12401.961199095 6941.9308823529) (10 12401.961199095 6926.84739819))
((0 . "LWPOLYLINE") (100 . "AcDbEntity") (8 . "PLANTS") (62 . 94) (370 . 13) (100 . "AcDbPolyline") (90 . 2) (70 . 0)
(43 . 0.0) (10 12401.961199095 6941.9308823529) (10 12413.2734162896 6994.7207013575))
((0 . "LWPOLYLINE") (100 . "AcDbEntity") (8 . "PLANTS") (62 . 94) (370 . 13) (100 . "AcDbPolyline") (90 . 2) (70 . 0)
(43 . 0.0) (10 12450.9799773756 6923.0769230769) (10 12401.961199095 6926.84739819))
((0 . "LWPOLYLINE") (100 . "AcDbEntity") (8 . "PLANTS") (62 . 94) (370 . 13) (100 . "AcDbPolyline") (90 . 3) (70 . 0)
(43 . 0.0) (10 12401.961199095 444.9462669683) (10 12424.3647058824 448.9384615385) (10 12450.9799773756
524.1317873303))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12409.5022624434 6512.0662895928 0.0) (10 12437.8766662961 6530.5971950781 0.0) (10 12422.6551200953
6564.3930627801 0.0) (10 12405.7311085973 6583.7104072398 0.0))
((0 . "LWPOLYLINE") (100 . "AcDbEntity") (8 . "PLANTS") (62 . 94) (370 . 13) (100 . "AcDbPolyline") (90 . 2) (70 . 0)
(43 . 0.0) (10 12409.5022624434 6598.7930995475) (10 12405.7311085973 6583.7104072398))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12405.7311085973 633.4841628959 0.0) (10 12442.1654583089 634.9934568416 0.0) (10 12446.1576605443
583.9550287304 0.0) (10 12481.146719457 580.6928733032 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12405.7311085973 633.4841628959 0.0) (10 12400.3136866438 589.0979649058 0.0) (10 12450.9029046319
567.3567901289 0.0) (10 12450.9799773756 524.1317873303 0.0))
((0 . "LWPOLYLINE") (100 . "AcDbEntity") (8 . "PLANTS") (62 . 94) (370 . 13) (100 . "AcDbPolyline") (90 . 3) (70 . 0)
(43 . 0.0) (10 12409.5022624434 6512.0662895928) (10 12413.125678733 6504.5183257919) (10 12413.2734162896
6481.9004524887))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12413.2734162896 7096.5306561086 0.0) (10 12394.2879287753 7068.3905087058 0.0) (10 12385.2955479207
7020.1171966551 0.0) (10 12413.2734162896 6994.7207013575 0.0))
((0 . "LWPOLYLINE") (100 . "AcDbEntity") (8 . "PLANTS") (62 . 94) (370 . 13) (100 . "AcDbPolyline") (90 . 2) (70 . 0)
(43 . 0.0) (10 12435.8978506787 6994.7207013575) (10 12413.2734162896 6994.7207013575))
((0 . "LWPOLYLINE") (100 . "AcDbEntity") (8 . "PLANTS") (62 . 94) (370 . 13) (100 . "AcDbPolyline") (90 . 2) (70 . 0)
(43 . 0.0) (10 12413.2734162896 6481.9004524887) (10 12481.1463046757 6481.9004524887))
((0 . "LWPOLYLINE") (100 . "AcDbEntity") (8 . "PLANTS") (62 . 94) (370 . 13) (100 . "AcDbPolyline") (90 . 3) (70 . 0)
(43 . 0.0) (10 12413.2734162896 6429.1101809955) (10 12414.47760181 6417.7979638009) (10 12432.1266968326
6402.7149321267))
((0 . "LWPOLYLINE") (100 . "AcDbEntity") (8 . "PLANTS") (62 . 94) (370 . 13) (100 . "AcDbPolyline") (90 . 2) (70 . 0)
(43 . 0.0) (10 12413.2734162896 6429.1101809955) (10 12424.5856334842 6436.6515837104))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12417.0433257919 6293.3635746606 0.0) (10 12405.3845225525 6311.7929830521 0.0) (10 12437.7426450226
6331.3345821603 0.0) (10 12413.2734162896 6349.9246606335 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.1594123849)
(40 . 0.2653367252) (40 . 1) (40 . 1) (40 . 1) (40 . 1) (10 12420.814479638 7111.6141402714 0.0) (10 12424.2148137393
7123.0553708516 0.0) (10 12439.1586274895 7130.3096027605 0.0) (10 12472.5562253464 7090.9532422411 0.0) (10
12416.5557799619 7031.8479160832 0.0) (10 12435.8978506787 7002.2624434389 0.0))
((0 . "LWPOLYLINE") (100 . "AcDbEntity") (8 . "PLANTS") (62 . 94) (370 . 13) (100 . "AcDbPolyline") (90 . 2) (70 . 0)
(43 . 0.0) (10 12424.5856334842 6779.7885746606) (10 12473.6044117647 6779.7885746606))
((0 . "LWPOLYLINE") (100 . "AcDbEntity") (8 . "PLANTS") (62 . 94) (370 . 13) (100 . "AcDbPolyline") (90 . 3) (70 . 0)
(43 . 0.0) (10 12439.667760181 6840.1209276018) (10 12425.642081448 6813.7252262443) (10 12424.5856334842
6779.7885746606))
((0 . "LWPOLYLINE") (100 . "AcDbEntity") (8 . "PLANTS") (62 . 94) (370 . 13) (100 . "AcDbPolyline") (90 . 2) (70 . 0)
(43 . 0.0) (10 12424.5856334842 6455.5052036199) (10 12424.5856334842 6436.6515837104))
((0 . "LWPOLYLINE") (100 . "AcDbEntity") (8 . "PLANTS") (62 . 94) (370 . 13) (100 . "AcDbPolyline") (90 . 3) (70 . 0)
(43 . 0.0) (10 12424.5856334842 6436.6515837104) (10 12435.7432126697 6425.3328054299) (10 12432.1266968326
6402.7149321267))
((0 . "LWPOLYLINE") (100 . "AcDbEntity") (8 . "PLANTS") (62 . 94) (370 . 13) (100 . "AcDbPolyline") (90 . 2) (70 . 0)
(43 . 0.0) (10 12469.8340408905 735.2941595786) (10 12428.3555429864 739.0639140271))
((0 . "LWPOLYLINE") (100 . "AcDbEntity") (8 . "PLANTS") (62 . 94) (370 . 13) (100 . "AcDbPolyline") (90 . 2) (70 . 0)
(43 . 0.0) (10 12435.8978506787 6395.1735294118) (10 12432.1266968326 6402.7149321267))
((0 . "LWPOLYLINE") (100 . "AcDbEntity") (8 . "PLANTS") (62 . 94) (370 . 13) (100 . "AcDbPolyline") (90 . 2) (70 . 0)
(43 . 0.0) (10 12435.8978506787 6994.7207013575) (10 12435.8978506787 7002.2624434389))
((0 . "LWPOLYLINE") (100 . "AcDbEntity") (8 . "PLANTS") (62 . 94) (370 . 13) (100 . "AcDbPolyline") (90 . 2) (70 . 0)
(43 . 0.0) (10 12435.8978506787 7002.2624434389) (10 12473.6044117647 7021.1164027149))
((0 . "LWPOLYLINE") (100 . "AcDbEntity") (8 . "PLANTS") (62 . 94) (370 . 13) (100 . "AcDbPolyline") (90 . 3) (70 . 0)
(43 . 0.0) (10 12435.8978506787 6994.7207013575) (10 12448.4142533937 6960.7909502262) (10 12458.5222850679
6953.2430995475))
((0 . "LWPOLYLINE") (100 . "AcDbEntity") (8 . "PLANTS") (62 . 94) (370 . 13) (100 . "AcDbPolyline") (90 . 2) (70 . 0)
(43 . 0.0) (10 12439.667760181 6840.1209276018) (10 12447.2100678733 6840.1209276018))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4173263972) (40
. 1) (40 . 1) (40 . 1) (40 . 1) (10 12445.3238687784 6630.8449095023 0.0) (10 12452.4298752487 6624.6656451633 0.0) (10
12456.2213428656 6595.8601724502 0.0) (10 12473.8708189692 6579.358177492 0.0) (10 12493.6015314751 6593.9974936829
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12445.3238687783 6630.8449095023 0.0) (10 12468.5986959366 6630.8465193805 0.0) (10 12474.4785296271
6664.8689051903 0.0) (10 12500 6655.3541855204 0.0))
((0 . "LWPOLYLINE") (100 . "AcDbEntity") (8 . "PLANTS") (62 . 94) (370 . 13) (100 . "AcDbPolyline") (90 . 3) (70 . 0)
(43 . 0.0) (10 12473.6044117647 6779.7885746606) (10 12472.5479638009 6809.9547511312) (10 12447.2100678733
6840.1209276018))
((0 . "LWPOLYLINE") (100 . "AcDbEntity") (8 . "PLANTS") (62 . 94) (370 . 13) (100 . "AcDbPolyline") (90 . 2) (70 . 0)
(43 . 0.0) (10 12462.2921945701 6870.2863122172) (10 12447.2100678733 6840.1209276018))
((0 . "LWPOLYLINE") (100 . "AcDbEntity") (8 . "PLANTS") (62 . 94) (370 . 13) (100 . "AcDbPolyline") (90 . 2) (70 . 0)
(43 . 0.0) (10 12462.2921945701 6870.2863122172) (10 12450.9799773756 6923.0769230769))
((0 . "LWPOLYLINE") (100 . "AcDbEntity") (8 . "PLANTS") (62 . 94) (370 . 13) (100 . "AcDbPolyline") (90 . 3) (70 . 0)
(43 . 0.0) (10 12458.5222850679 6953.2430995475) (10 12457.4728506787 6938.1596153846) (10 12450.9799773756
6923.0769230769))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3806846989) (40
. 1) (40 . 1) (40 . 1) (40 . 1) (10 12537.7078054299 441.1764705883 0.0) (10 12543.1400517642 460.7825653443 0.0) (10
12507.6297983469 484.4555289266 0.0) (10 12477.0399440698 520.2882536477 0.0) (10 12450.9799773756 524.1317873304 0.0))
((0 . "LWPOLYLINE") (100 . "AcDbEntity") (8 . "PLANTS") (62 . 94) (370 . 13) (100 . "AcDbPolyline") (90 . 3) (70 . 0)
(43 . 0.0) (10 12458.5222850679 6953.2430995475) (10 12511.3122171946 6991.0985294118) (10 12526.3955882353
7009.8041855204))
((0 . "LWPOLYLINE") (100 . "AcDbEntity") (8 . "PLANTS") (62 . 94) (370 . 13) (100 . "AcDbPolyline") (90 . 2) (70 . 0)
(43 . 0.0) (10 12462.2921945701 6870.2863122172) (10 12481.146719457 6870.2863122172))
((0 . "LWPOLYLINE") (100 . "AcDbEntity") (8 . "PLANTS") (62 . 94) (370 . 13) (100 . "AcDbPolyline") (90 . 2) (70 . 0)
(43 . 0.0) (10 12462.2921945701 384.6153846154) (10 12481.146719457 384.6153846154))
((0 . "LWPOLYLINE") (100 . "AcDbEntity") (8 . "PLANTS") (62 . 94) (370 . 13) (100 . "AcDbPolyline") (90 . 2) (70 . 0)
(43 . 0.0) (10 12469.8345022624 618.4021493213) (10 12481.146719457 580.6928733032))
((0 . "LWPOLYLINE") (100 . "AcDbEntity") (8 . "PLANTS") (62 . 94) (370 . 13) (100 . "AcDbPolyline") (90 . 2) (70 . 0)
(43 . 0.0) (10 12469.8345022624 252.6385746606) (10 12469.8345022624 267.7234162896))
((0 . "LWPOLYLINE") (100 . "AcDbEntity") (8 . "PLANTS") (62 . 94) (370 . 13) (100 . "AcDbPolyline") (90 . 3) (70 . 0)
(43 . 0.0) (10 12469.8345022624 267.7234162896) (10 12469.9823529412 309.1947963801) (10 12473.6044117647
316.742081448))
((0 . "LWPOLYLINE") (100 . "AcDbEntity") (8 . "PLANTS") (62 . 94) (370 . 13) (100 . "AcDbPolyline") (90 . 2) (70 . 0)
(43 . 0.0) (10 12511.3122171946 279.0356334842) (10 12469.8345022624 267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12469.8345022624 252.6385746606 0.0) (10 12494.9744435807 222.807850861 0.0) (10 12555.1524847305
225.8589990582 0.0) (10 12579.185520362 256.411199095 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12526.5447868356 7100.6338490172 0.0) (10 12505.3791861315 7082.5024423895 0.0) (10 12465.4642734152
7056.7621199967 0.0) (10 12473.6044117647 7021.1164027149 0.0))
((0 . "LWPOLYLINE") (100 . "AcDbEntity") (8 . "PLANTS") (62 . 94) (370 . 13) (100 . "AcDbPolyline") (90 . 3) (70 . 0)
(43 . 0.0) (10 12526.3955882353 7021.1164027149) (10 12515.0833710407 7024.7320135747) (10 12473.6044117647
7021.1164027149))
((0 . "LWPOLYLINE") (100 . "AcDbEntity") (8 . "PLANTS") (62 . 94) (370 . 13) (100 . "AcDbPolyline") (90 . 2) (70 . 0)
(43 . 0.0) (10 12473.6044117647 6779.7885746606) (10 12481.146719457 6772.2476244344))
((0 . "LWPOLYLINE") (100 . "AcDbEntity") (8 . "PLANTS") (62 . 94) (370 . 13) (100 . "AcDbPolyline") (90 . 3) (70 . 0)
(43 . 0.0) (10 12500 358.2211538462) (10 12482.2031674208 343.1314479638) (10 12473.6044117647 316.742081448))
((0 . "LWPOLYLINE") (100 . "AcDbEntity") (8 . "PLANTS") (62 . 94) (370 . 13) (100 . "AcDbPolyline") (90 . 3) (70 . 0)
(43 . 0.0) (10 12473.6044117647 316.742081448) (10 12499.845361991 328.2027149321) (10 12507.5410633484 354.4485294118))
((0 . "LWPOLYLINE") (100 . "AcDbEntity") (8 . "PLANTS") (62 . 94) (370 . 13) (100 . "AcDbPolyline") (90 . 2) (70 . 0)
(43 . 0.0) (10 12484.9166289593 6738.3109728507) (10 12477.3755656109 6742.0814479638))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4559303794) (40
. 1) (40 . 1) (40 . 1) (40 . 1) (10 12477.3755656109 6742.0814479638 0.0) (10 12457.2347702111 6750.1367176489 0.0) (10
12429.4683795333 6726.6728004465 0.0) (10 12468.2758950318 6696.2432271417 0.0) (10 12484.9166289593 6708.1447963801
0.0))
((0 . "LWPOLYLINE") (100 . "AcDbEntity") (8 . "PLANTS") (62 . 94) (370 . 13) (100 . "AcDbPolyline") (90 . 2) (70 . 0)
(43 . 0.0) (10 12477.3755656109 6742.0814479638) (10 12481.146719457 6772.2476244344))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12609.3510180996 6851.4331447963 0.0) (10 12576.9845323414 6814.3627302944 0.0) (10 12506.5612845324
6834.2501707753 0.0) (10 12481.146719457 6870.2863122171 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12549.0200226244 6889.1402714932 0.0) (10 12525.4560562629 6873.7319999828 0.0) (10 12493.6172596982
6914.7962226051 0.0) (10 12481.146719457 6870.2863122172 0.0))
((0 . "LWPOLYLINE") (100 . "AcDbEntity") (8 . "PLANTS") (62 . 94) (370 . 13) (100 . "AcDbPolyline") (90 . 2) (70 . 0)
(43 . 0.0) (10 12518.853280543 6783.559841629) (10 12481.146719457 6772.2476244344))
((0 . "LWPOLYLINE") (100 . "AcDbEntity") (8 . "PLANTS") (62 . 94) (370 . 13) (100 . "AcDbPolyline") (90 . 3) (70 . 0)
(43 . 0.0) (10 12590.4977375566 441.1764705882) (10 12545.1011312217 505.2799773756) (10 12481.146719457
580.6928733032))
((0 . "LWPOLYLINE") (100 . "AcDbEntity") (8 . "PLANTS") (62 . 94) (370 . 13) (100 . "AcDbPolyline") (90 . 2) (70 . 0)
(43 . 0.0) (10 12500 358.2211538462) (10 12481.146719457 384.6153846154))
((0 . "LWPOLYLINE") (100 . "AcDbEntity") (8 . "PLANTS") (62 . 94) (370 . 13) (100 . "AcDbPolyline") (90 . 2) (70 . 0)
(43 . 0.0) (10 12484.9166289593 399.69739819) (10 12481.146719457 384.6153846154))
((0 . "LWPOLYLINE") (100 . "AcDbEntity") (8 . "PLANTS") (62 . 94) (370 . 13) (100 . "AcDbPolyline") (90 . 2) (70 . 0)
(43 . 0.0) (10 12484.9166289593 6738.3109728507) (10 12484.9166289593 6708.1447963801))
((0 . "LWPOLYLINE") (100 . "AcDbEntity") (8 . "PLANTS") (62 . 94) (370 . 13) (100 . "AcDbPolyline") (90 . 3) (70 . 0)
(43 . 0.0) (10 12484.9166289593 6738.3109728507) (10 12537.7078054299 6749.4683257919) (10 12579.185520362
6749.6231900452))
((0 . "LWPOLYLINE") (100 . "AcDbEntity") (8 . "PLANTS") (62 . 94) (370 . 13) (100 . "AcDbPolyline") (90 . 3) (70 . 0)
(43 . 0.0) (10 12484.9166289593 6708.1447963801) (10 12498.9436651584 6685.520361991) (10 12500 6655.3541855204))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12507.5410633484 429.8642533937 0.0) (10 12489.075567439 455.3868647258 0.0) (10 12449.5765340194
411.98373732 0.0) (10 12484.9166289593 399.69739819 0.0))
((0 . "LWPOLYLINE") (100 . "AcDbEntity") (8 . "PLANTS") (62 . 94) (370 . 13) (100 . "AcDbPolyline") (90 . 3) (70 . 0)
(43 . 0.0) (10 12507.5410633484 429.8642533937) (10 12499.845361991 411.0171945701) (10 12484.9166289593 399.69739819))
((0 . "LWPOLYLINE") (100 . "AcDbEntity") (8 . "PLANTS") (62 . 94) (370 . 13) (100 . "AcDbPolyline") (90 . 2) (70 . 0)
(43 . 0.0) (10 12501.042206785 707.2068102736) (10 12488.6877828054 708.8998868778))
((0 . "LWPOLYLINE") (100 . "AcDbEntity") (8 . "PLANTS") (62 . 94) (370 . 13) (100 . "AcDbPolyline") (90 . 2) (70 . 0)
(43 . 0.0) (10 12496.2288461538 6930.6186651584) (10 12545.2488687783 6938.1596153846))
((0 . "LWPOLYLINE") (100 . "AcDbEntity") (8 . "PLANTS") (62 . 94) (370 . 13) (100 . "AcDbPolyline") (90 . 2) (70 . 0)
(43 . 0.0) (10 12500 358.2211538462) (10 12507.5410633484 354.4485294118))
((0 . "LWPOLYLINE") (100 . "AcDbEntity") (8 . "PLANTS") (62 . 94) (370 . 13) (100 . "AcDbPolyline") (90 . 2) (70 . 0)
(43 . 0.0) (10 12518.853280543 6783.559841629) (10 12507.5410633484 6809.9547511312))
((0 . "LWPOLYLINE") (100 . "AcDbEntity") (8 . "PLANTS") (62 . 94) (370 . 13) (100 . "AcDbPolyline") (90 . 2) (70 . 0)
(43 . 0.0) (10 12507.5410633484 429.8642533937) (10 12537.7078054299 441.1764705882))
((0 . "LWPOLYLINE") (100 . "AcDbEntity") (8 . "PLANTS") (62 . 94) (370 . 13) (100 . "AcDbPolyline") (90 . 2) (70 . 0)
(43 . 0.0) (10 12515.0833710407 354.4485294118) (10 12507.5410633484 354.4485294118))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12511.3122171946 279.0356334842 0.0) (10 12528.2024791461 264.7108741343 0.0) (10 12551.0109484026
297.5051522894 0.0) (10 12560.332239819 301.6600678733 0.0))
((0 . "LWPOLYLINE") (100 . "AcDbEntity") (8 . "PLANTS") (62 . 94) (370 . 13) (100 . "AcDbPolyline") (90 . 3) (70 . 0)
(43 . 0.0) (10 12541.4777149321 324.2845022624) (10 12516.2806561086 301.6524886878) (10 12511.3122171946
279.0356334842))
((0 . "LWPOLYLINE") (100 . "AcDbEntity") (8 . "PLANTS") (62 . 94) (370 . 13) (100 . "AcDbPolyline") (90 . 3) (70 . 0)
(43 . 0.0) (10 12515.0833710407 354.4485294118) (10 12530.1654977376 340.4228506787) (10 12541.4777149321
335.596719457))
((0 . "LWPOLYLINE") (100 . "AcDbEntity") (8 . "PLANTS") (62 . 94) (370 . 13) (100 . "AcDbPolyline") (90 . 3) (70 . 0)
(43 . 0.0) (10 12515.0833710407 354.4485294118) (10 12559.1337104072 411.0096153846) (10 12564.1021493213
429.8642533937))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12658.371040724 6779.7885746607 0.0) (10 12611.8359367141 6788.7962163897 0.0) (10 12565.716094939
6776.354743887 0.0) (10 12518.853280543 6783.559841629 0.0))
((0 . "LWPOLYLINE") (100 . "AcDbEntity") (8 . "PLANTS") (62 . 94) (370 . 13) (100 . "AcDbPolyline") (90 . 3) (70 . 0)
(43 . 0.0) (10 13069.3820135747 6478.129638009) (10 13020.3619909502 6481.8938914027) (10 12951.9137930311
6481.8947936744))
((0 . "LWPOLYLINE") (100 . "AcDbEntity") (8 . "PLANTS") (62 . 94) (370 . 13) (100 . "AcDbPolyline") (90 . 2) (70 . 0)
(43 . 0.0) (10 12526.3955882353 7021.1164027149) (10 12526.3955882353 7009.8041855204))
((0 . "LWPOLYLINE") (100 . "AcDbEntity") (8 . "PLANTS") (62 . 94) (370 . 13) (100 . "AcDbPolyline") (90 . 2) (70 . 0)
(43 . 0.0) (10 12530.1654977376 7032.4286199095) (10 12526.3955882353 7021.1164027149))
((0 . "LWPOLYLINE") (100 . "AcDbEntity") (8 . "PLANTS") (62 . 94) (370 . 13) (100 . "AcDbPolyline") (90 . 2) (70 . 0)
(43 . 0.0) (10 12567.8733031674 7006.032918552) (10 12526.3955882353 7009.8041855204))
((0 . "LWPOLYLINE") (100 . "AcDbEntity") (8 . "PLANTS") (62 . 94) (370 . 13) (100 . "AcDbPolyline") (90 . 2) (70 . 0)
(43 . 0.0) (10 12537.7078054299 441.1764705882) (10 12564.1021493213 429.8642533937))
((0 . "LWPOLYLINE") (100 . "AcDbEntity") (8 . "PLANTS") (62 . 94) (370 . 13) (100 . "AcDbPolyline") (90 . 2) (70 . 0)
(43 . 0.0) (10 12541.4777149321 324.2845022624) (10 12541.4777149321 335.596719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12586.7265837104 339.3665158371 0.0) (10 12581.2386067882 361.4600772714 0.0) (10 12547.8584282435
348.4777689476 0.0) (10 12541.4777149321 335.596719457 0.0))
((0 . "LWPOLYLINE") (100 . "AcDbEntity") (8 . "PLANTS") (62 . 94) (370 . 13) (100 . "AcDbPolyline") (90 . 2) (70 . 0)
(43 . 0.0) (10 12541.4777149321 324.2845022624) (10 12560.332239819 301.6600678733))
((0 . "LWPOLYLINE") (100 . "AcDbEntity") (8 . "PLANTS") (62 . 94) (370 . 13) (100 . "AcDbPolyline") (90 . 3) (70 . 0)
(43 . 0.0) (10 12549.0200226244 6889.1402714932) (10 12552.4943438914 6923.0769230769) (10 12545.2488687783
6938.1596153846))
((0 . "LWPOLYLINE") (100 . "AcDbEntity") (8 . "PLANTS") (62 . 94) (370 . 13) (100 . "AcDbPolyline") (90 . 2) (70 . 0)
(43 . 0.0) (10 12579.185520362 6972.0962669683) (10 12545.2488687783 6938.1596153846))
((0 . "LWPOLYLINE") (100 . "AcDbEntity") (8 . "PLANTS") (62 . 94) (370 . 13) (100 . "AcDbPolyline") (90 . 3) (70 . 0)
(43 . 0.0) (10 12594.2688914027 6881.5985294118) (10 12560.332239819 6881.7533936652) (10 12549.0200226244
6889.1402714932))
((0 . "LWPOLYLINE") (100 . "AcDbEntity") (8 . "PLANTS") (62 . 94) (370 . 13) (100 . "AcDbPolyline") (90 . 2) (70 . 0)
(43 . 0.0) (10 12560.332239819 301.6600678733) (10 12567.8733031674 301.6600678733))
((0 . "LWPOLYLINE") (100 . "AcDbEntity") (8 . "PLANTS") (62 . 94) (370 . 13) (100 . "AcDbPolyline") (90 . 3) (70 . 0)
(43 . 0.0) (10 12564.2015214544 7089.3368286316) (10 12564.2498868778 7073.9062217195) (10 12571.6444570136
7036.1990950226))
((0 . "LWPOLYLINE") (100 . "AcDbEntity") (8 . "PLANTS") (62 . 94) (370 . 13) (100 . "AcDbPolyline") (90 . 2) (70 . 0)
(43 . 0.0) (10 12564.1021493213 527.9044117647) (10 12579.185520362 527.9044117647))
((0 . "LWPOLYLINE") (100 . "AcDbEntity") (8 . "PLANTS") (62 . 94) (370 . 13) (100 . "AcDbPolyline") (90 . 3) (70 . 0)
(43 . 0.0) (10 12590.4977375566 441.1764705882) (10 12579.185520362 431.0691176471) (10 12564.1021493213
429.8642533937))
((0 . "LWPOLYLINE") (100 . "AcDbEntity") (8 . "PLANTS") (62 . 94) (370 . 13) (100 . "AcDbPolyline") (90 . 2) (70 . 0)
(43 . 0.0) (10 12579.185520362 6972.0962669683) (10 12567.8733031674 7006.032918552))
((0 . "LWPOLYLINE") (100 . "AcDbEntity") (8 . "PLANTS") (62 . 94) (370 . 13) (100 . "AcDbPolyline") (90 . 2) (70 . 0)
(43 . 0.0) (10 12567.8733031674 7006.032918552) (10 12571.6444570136 7036.1990950226))
((0 . "LWPOLYLINE") (100 . "AcDbEntity") (8 . "PLANTS") (62 . 94) (370 . 13) (100 . "AcDbPolyline") (90 . 2) (70 . 0)
(43 . 0.0) (10 12579.185520362 256.411199095) (10 12567.8733031674 301.6600678733))
((0 . "LWPOLYLINE") (100 . "AcDbEntity") (8 . "PLANTS") (62 . 94) (370 . 13) (100 . "AcDbPolyline") (90 . 2) (70 . 0)
(43 . 0.0) (10 12586.7265837104 339.3665158371) (10 12567.8733031674 301.6600678733))
((0 . "LWPOLYLINE") (100 . "AcDbEntity") (8 . "PLANTS") (62 . 94) (370 . 13) (100 . "AcDbPolyline") (90 . 2) (70 . 0)
(43 . 0.0) (10 12605.5811085973 7028.6573529412) (10 12571.6444570136 7036.1990950226))
((0 . "LWPOLYLINE") (100 . "AcDbEntity") (8 . "PLANTS") (62 . 94) (370 . 13) (100 . "AcDbPolyline") (90 . 2) (70 . 0)
(43 . 0.0) (10 12579.185520362 6972.0962669683) (10 12601.8099547511 6972.0962669683))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12601.8099547511 441.1764705882 0.0) (10 12622.0737754096 468.5717478352 0.0) (10 12603.2177340113
509.6369440891 0.0) (10 12579.185520362 527.9044117647 0.0))
((0 . "LWPOLYLINE") (100 . "AcDbEntity") (8 . "PLANTS") (62 . 94) (370 . 13) (100 . "AcDbPolyline") (90 . 2) (70 . 0)
(43 . 0.0) (10 12579.185520362 527.9044117647) (10 12582.9566742081 550.5288461538))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12579.185520362 256.411199095 0.0) (10 12607.8746825466 242.0995851896 0.0) (10 12663.5338716626
219.0529423725 0.0) (10 12684.7666289593 260.1809954751 0.0))
((0 . "LWPOLYLINE") (100 . "AcDbEntity") (8 . "PLANTS") (62 . 94) (370 . 13) (100 . "AcDbPolyline") (90 . 3) (70 . 0)
(43 . 0.0) (10 12582.9566742081 550.5288461538) (10 12598.038800905 550.3804298643) (10 12635.7466063348
539.2166289593))
((0 . "LWPOLYLINE") (100 . "AcDbEntity") (8 . "PLANTS") (62 . 94) (370 . 13) (100 . "AcDbPolyline") (90 . 2) (70 . 0)
(43 . 0.0) (10 12613.1221719457 335.596719457) (10 12586.7265837104 339.3665158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12591.9027667226 863.3671858457 0.0) (10 12609.5122216873 865.6639003192 0.0) (10 12622.651193629
846.6875024816 0.0) (10 12628.8993091035 833.5599868183 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12714.7437327953 607.2428698129 0.0) (10 12730.58199255 567.0171001029 0.0) (10 12716.600088175
494.8841543152 0.0) (10 12665.9121040724 486.4253393665 0.0))
((0 . "SPLINE") (100 . "AcDbEntity") (8 . "PLANTS") (62 . 94) (370 . 13) (100 . "AcDbSpline") (70 . 0) (71 . 3) (72 .
12) (73 . 8) (74 . 0) (42 . 0.0000001) (43 . 0.0000001) (40 . 0.0) (40 . 0.0) (40 . 0.0) (40 . 0.0) (40 . 0.2674064215)
(40 . 0.4100274662) (40 . 0.5014863593) (40 . 0.654584041) (40 . 1) (40 . 1) (40 . 1) (40 . 1) (10 12635.7466063348
584.4654977375 0.0) (10 12613.7897119722 599.5477502408 0.0) (10 12630.6978182176 642.2411929596 0.0) (10
12616.2109289511 685.582492324 0.0) (10 12605.5661282808 718.2499777494 0.0) (10 12605.7870570739 771.3754190617 0.0)
(10 12581.221785582 812.4797319385 0.0) (10 12587.6277618668 845.4121654515 0.0))
((0 . "LWPOLYLINE") (100 . "AcDbEntity") (8 . "PLANTS") (62 . 94) (370 . 13) (100 . "AcDbPolyline") (90 . 2) (70 . 0)
(43 . 0.0) (10 12594.2688914027 871.0407239819) (10 12593.2397021333 868.9823145708))
((0 . "LWPOLYLINE") (100 . "AcDbEntity") (8 . "PLANTS") (62 . 94) (370 . 13) (100 . "AcDbPolyline") (90 . 2) (70 . 0)
(43 . 0.0) (10 12601.8099547511 441.1764705882) (10 12590.4977375566 441.1764705882))
((0 . "LWPOLYLINE") (100 . "AcDbEntity") (8 . "PLANTS") (62 . 94) (370 . 13) (100 . "AcDbPolyline") (90 . 2) (70 . 0)
(43 . 0.0) (10 12594.2688914027 6881.5985294118) (10 12609.3510180995 6851.4331447964))
((0 . "LWPOLYLINE") (100 . "AcDbEntity") (8 . "PLANTS") (62 . 94) (370 . 13) (100 . "AcDbPolyline") (90 . 3) (70 . 0)
(43 . 0.0) (10 12594.2688914027 6881.5985294118) (10 12597.1438914027 6900.4459276018) (10 12609.3510180995
6911.7647058824))
((0 . "LWPOLYLINE") (100 . "AcDbEntity") (8 . "PLANTS") (62 . 94) (370 . 13) (100 . "AcDbPolyline") (90 . 2) (70 . 0)
(43 . 0.0) (10 12609.3510180995 6957.0135746606) (10 12601.8099547511 6972.0962669683))
((0 . "LWPOLYLINE") (100 . "AcDbEntity") (8 . "PLANTS") (62 . 94) (370 . 13) (100 . "AcDbPolyline") (90 . 2) (70 . 0)
(43 . 0.0) (10 12601.8099547511 6972.0962669683) (10 12613.1221719457 6994.7207013575))
((0 . "LWPOLYLINE") (100 . "AcDbEntity") (8 . "PLANTS") (62 . 94) (370 . 13) (100 . "AcDbPolyline") (90 . 2) (70 . 0)
(43 . 0.0) (10 12620.6632352941 411.0096153846) (10 12601.8099547511 441.1764705882))
((0 . "LWPOLYLINE") (100 . "AcDbEntity") (8 . "PLANTS") (62 . 94) (370 . 13) (100 . "AcDbPolyline") (90 . 2) (70 . 0)
(43 . 0.0) (10 12605.5811085973 7028.6573529412) (10 12613.1221719457 6994.7207013575))
((0 . "LWPOLYLINE") (100 . "AcDbEntity") (8 . "PLANTS") (62 . 94) (370 . 13) (100 . "AcDbPolyline") (90 . 2) (70 . 0)
(43 . 0.0) (10 12605.5811085973 7028.6573529412) (10 12620.6632352941 7036.1990950226))
((0 . "LWPOLYLINE") (100 . "AcDbEntity") (8 . "PLANTS") (62 . 94) (370 . 13) (100 . "AcDbPolyline") (90 . 3) (70 . 0)
(43 . 0.0) (10 12609.3510180995 6957.0135746606) (10 12605.5880090498 6934.3891402715) (10 12609.3510180995
6911.7647058824))
((0 . "LWPOLYLINE") (100 . "AcDbEntity") (8 . "PLANTS") (62 . 94) (370 . 13) (100 . "AcDbPolyline") (90 . 3) (70 . 0)
(43 . 0.0) (10 12609.3510180995 6957.0135746606) (10 12635.5919683258 6961.9883484163) (10 12643.2876696833
6983.4084841629))
((0 . "LWPOLYLINE") (100 . "AcDbEntity") (8 . "PLANTS") (62 . 94) (370 . 13) (100 . "AcDbPolyline") (90 . 2) (70 . 0)
(43 . 0.0) (10 12647.0588235294 6907.9942307692) (10 12609.3510180995 6911.7647058824))
((0 . "LWPOLYLINE") (100 . "AcDbEntity") (8 . "PLANTS") (62 . 94) (370 . 13) (100 . "AcDbPolyline") (90 . 2) (70 . 0)
(43 . 0.0) (10 12647.0588235294 6851.4331447964) (10 12609.3510180995 6851.4331447964))
((0 . "LWPOLYLINE") (100 . "AcDbEntity") (8 . "PLANTS") (62 . 94) (370 . 13) (100 . "AcDbPolyline") (90 . 3) (70 . 0)
(43 . 0.0) (10 12643.2876696833 6983.4084841629) (10 12639.3631221719 6989.7524886878) (10 12613.1221719457
6994.7207013575))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12613.1221719457 335.596719457 0.0) (10 12614.4414014849 303.4882866579 0.0) (10 12648.2745935454
275.9490789444 0.0) (10 12677.2243212669 267.7234162896 0.0))
((0 . "LWPOLYLINE") (100 . "AcDbEntity") (8 . "PLANTS") (62 . 94) (370 . 13) (100 . "AcDbPolyline") (90 . 2) (70 . 0)
(43 . 0.0) (10 12613.1221719457 335.596719457) (10 12631.9754524887 354.4485294118))
((0 . "LWPOLYLINE") (100 . "AcDbEntity") (8 . "PLANTS") (62 . 94) (370 . 13) (100 . "AcDbPolyline") (90 . 2) (70 . 0)
(43 . 0.0) (10 12654.5998868778 7032.4286199095) (10 12620.6632352941 7036.1990950226))
((0 . "LWPOLYLINE") (100 . "AcDbEntity") (8 . "PLANTS") (62 . 94) (370 . 13) (100 . "AcDbPolyline") (90 . 3) (70 . 0)
(43 . 0.0) (10 12630.8037397497 7094.3458845027) (10 12621.7195701357 7077.6774886878) (10 12620.6632352941
7036.1990950226))
((0 . "LWPOLYLINE") (100 . "AcDbEntity") (8 . "PLANTS") (62 . 94) (370 . 13) (100 . "AcDbPolyline") (90 . 3) (70 . 0)
(43 . 0.0) (10 12620.6632352941 411.0096153846) (10 12665.9121040724 396.9770361991) (10 12680.9954751131 395.92760181))
((0 . "LWPOLYLINE") (100 . "AcDbEntity") (8 . "PLANTS") (62 . 94) (370 . 13) (100 . "AcDbPolyline") (90 . 3) (70 . 0)
(43 . 0.0) (10 12620.6632352941 411.0096153846) (10 12620.8109728507 395.92760181) (10 12631.9754524887 354.4485294118))
((0 . "LWPOLYLINE") (100 . "AcDbEntity") (8 . "PLANTS") (62 . 94) (370 . 13) (100 . "AcDbPolyline") (90 . 2) (70 . 0)
(43 . 0.0) (10 12650.8299773756 354.4485294118) (10 12631.9754524887 354.4485294118))
((0 . "LWPOLYLINE") (100 . "AcDbEntity") (8 . "PLANTS") (62 . 94) (370 . 13) (100 . "AcDbPolyline") (90 . 2) (70 . 0)
(43 . 0.0) (10 12635.7466063348 584.4654977376) (10 12650.8299773756 584.4654977376))
((0 . "LWPOLYLINE") (100 . "AcDbEntity") (8 . "PLANTS") (62 . 94) (370 . 13) (100 . "AcDbPolyline") (90 . 2) (70 . 0)
(43 . 0.0) (10 12635.7466063348 584.4654977376) (10 12635.7466063348 539.2166289593))
((0 . "LWPOLYLINE") (100 . "AcDbEntity") (8 . "PLANTS") (62 . 94) (370 . 13) (100 . "AcDbPolyline") (90 . 2) (70 . 0)
(43 . 0.0) (10 12654.5998868778 531.6742081448) (10 12635.7466063348 539.2166289593))
((0 . "LWPOLYLINE") (100 . "AcDbEntity") (8 . "PLANTS") (62 . 94) (370 . 13) (100 . "AcDbPolyline") (90 . 2) (70 . 0)
(43 . 0.0) (10 12639.517760181 705.1272624434) (10 12639.517760181 712.6696832579))
((0 . "LWPOLYLINE") (100 . "AcDbEntity") (8 . "PLANTS") (62 . 94) (370 . 13) (100 . "AcDbPolyline") (90 . 2) (70 . 0)
(43 . 0.0) (10 12650.8299773756 6987.1797511312) (10 12643.2876696833 6983.4084841629))
((0 . "LWPOLYLINE") (100 . "AcDbEntity") (8 . "PLANTS") (62 . 94) (370 . 13) (100 . "AcDbPolyline") (90 . 2) (70 . 0)
(43 . 0.0) (10 12647.0588235294 6907.9942307692) (10 12650.8299773756 6896.6820135747))
((0 . "LWPOLYLINE") (100 . "AcDbEntity") (8 . "PLANTS") (62 . 94) (370 . 13) (100 . "AcDbPolyline") (90 . 2) (70 . 0)
(43 . 0.0) (10 12662.1421945701 6934.3891402715) (10 12647.0588235294 6907.9942307692))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12647.0588235294 6851.4331447964 0.0) (10 12664.9393063928 6834.5517836897 0.0) (10 12693.5559570576
6839.88409262 0.0) (10 12714.9321266968 6847.6618778281 0.0))
((0 . "LWPOLYLINE") (100 . "AcDbEntity") (8 . "PLANTS") (62 . 94) (370 . 13) (100 . "AcDbPolyline") (90 . 2) (70 . 0)
(43 . 0.0) (10 12647.0588235294 6851.4331447964) (10 12650.8299773756 6896.6820135747))
((0 . "LWPOLYLINE") (100 . "AcDbEntity") (8 . "PLANTS") (62 . 94) (370 . 13) (100 . "AcDbPolyline") (90 . 2) (70 . 0)
(43 . 0.0) (10 12684.7666289593 6896.6820135747) (10 12650.8299773756 6896.6820135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12650.8299773756 584.4654977376 0.0) (10 12668.4182722264 572.4902479396 0.0) (10 12666.0589926346
546.6327616532 0.0) (10 12654.5998868778 531.6742081448 0.0))
((0 . "LWPOLYLINE") (100 . "AcDbEntity") (8 . "PLANTS") (62 . 94) (370 . 13) (100 . "AcDbPolyline") (90 . 3) (70 . 0)
(43 . 0.0) (10 12673.4544117647 629.7143665158) (10 12655.803959276 618.2537330317) (10 12650.8299773756
584.4654977376))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12650.8299773756 354.4485294118 0.0) (10 12649.6650615332 321.9237401891 0.0) (10 12679.2587018768
300.1523375666 0.0) (10 12677.224321267 267.7234162896 0.0))
((0 . "LWPOLYLINE") (100 . "AcDbEntity") (8 . "PLANTS") (62 . 94) (370 . 13) (100 . "AcDbPolyline") (90 . 2) (70 . 0)
(43 . 0.0) (10 12684.7666289593 373.3031674208) (10 12650.8299773756 354.4485294118))
((0 . "LWPOLYLINE") (100 . "AcDbEntity") (8 . "PLANTS") (62 . 94) (370 . 13) (100 . "AcDbPolyline") (90 . 2) (70 . 0)
(43 . 0.0) (10 12665.9121040724 7021.1164027149) (10 12654.5998868778 7032.4286199095))
((0 . "LWPOLYLINE") (100 . "AcDbEntity") (8 . "PLANTS") (62 . 94) (370 . 13) (100 . "AcDbPolyline") (90 . 2) (70 . 0)
(43 . 0.0) (10 12654.5998868778 7032.4286199095) (10 12658.371040724 7055.0530542986))
((0 . "LWPOLYLINE") (100 . "AcDbEntity") (8 . "PLANTS") (62 . 94) (370 . 13) (100 . "AcDbPolyline") (90 . 3) (70 . 0)
(43 . 0.0) (10 12654.5998868778 531.6742081448) (10 12658.525678733 497.7375565611) (10 12665.9121040724
486.4253393665))
((0 . "LWPOLYLINE") (100 . "AcDbEntity") (8 . "PLANTS") (62 . 94) (370 . 13) (100 . "AcDbPolyline") (90 . 2) (70 . 0)
(43 . 0.0) (10 12658.371040724 6779.7885746606) (10 12662.1421945701 6753.3936651584))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6480463348) (40
. 1) (40 . 1) (40 . 1) (40 . 1) (10 12658.371040724 6779.7885746607 0.0) (10 12718.3031908307 6790.3039946513 0.0) (10
12812.3815300083 6780.5147207024 0.0) (10 12904.5440472318 6781.0755183013 0.0) (10 12937.4053167421 6779.7885746607
0.0))
((0 . "LWPOLYLINE") (100 . "AcDbEntity") (8 . "PLANTS") (62 . 94) (370 . 13) (100 . "AcDbPolyline") (90 . 2) (70 . 0)
(43 . 0.0) (10 12662.1421945701 6934.3891402715) (10 12684.7666289593 6930.6186651584))
((0 . "LWPOLYLINE") (100 . "AcDbEntity") (8 . "PLANTS") (62 . 94) (370 . 13) (100 . "AcDbPolyline") (90 . 2) (70 . 0)
(43 . 0.0) (10 12662.1421945701 6934.3891402715) (10 12665.9121040724 6941.9308823529))
((0 . "LWPOLYLINE") (100 . "AcDbEntity") (8 . "PLANTS") (62 . 94) (370 . 13) (100 . "AcDbPolyline") (90 . 3) (70 . 0)
(43 . 0.0) (10 12680.9954751131 395.92760181) (10 12669.8309954751 441.1764705882) (10 12665.9121040724 486.4253393665))
((0 . "LWPOLYLINE") (100 . "AcDbEntity") (8 . "PLANTS") (62 . 94) (370 . 13) (100 . "AcDbPolyline") (90 . 2) (70 . 0)
(43 . 0.0) (10 12677.224321267 267.7234162896) (10 12684.7666289593 260.1809954751))
((0 . "LWPOLYLINE") (100 . "AcDbEntity") (8 . "PLANTS") (62 . 94) (370 . 13) (100 . "AcDbPolyline") (90 . 2) (70 . 0)
(43 . 0.0) (10 12684.7666289593 373.3031674208) (10 12680.9954751131 395.92760181))
((0 . "LWPOLYLINE") (100 . "AcDbEntity") (8 . "PLANTS") (62 . 94) (370 . 13) (100 . "AcDbPolyline") (90 . 2) (70 . 0)
(43 . 0.0) (10 12684.7666289593 6896.6820135747) (10 12684.7666289593 6930.6186651584))
((0 . "LWPOLYLINE") (100 . "AcDbEntity") (8 . "PLANTS") (62 . 94) (370 . 13) (100 . "AcDbPolyline") (90 . 3) (70 . 0)
(43 . 0.0) (10 12684.7666289593 6930.6186651584) (10 12693.5118778281 6957.0135746606) (10 12707.3910633484
6968.3257918552))
((0 . "LWPOLYLINE") (100 . "AcDbEntity") (8 . "PLANTS") (62 . 94) (370 . 13) (100 . "AcDbPolyline") (90 . 2) (70 . 0)
(43 . 0.0) (10 12684.7666289593 6896.6820135747) (10 12707.3910633484 6896.6820135747))
((0 . "LWPOLYLINE") (100 . "AcDbEntity") (8 . "PLANTS") (62 . 94) (370 . 13) (100 . "AcDbPolyline") (90 . 3) (70 . 0)
(43 . 0.0) (10 12684.7666289593 373.3031674208) (10 12697.2761312217 328.060520362) (10 12722.4731900452
309.1996606335))
((0 . "LWPOLYLINE") (100 . "AcDbEntity") (8 . "PLANTS") (62 . 94) (370 . 13) (100 . "AcDbPolyline") (90 . 2) (70 . 0)
(43 . 0.0) (10 12696.0788461538 260.1809954751) (10 12684.7666289593 260.1809954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12688.5365384615 7032.4286199095 0.0) (10 12678.3092294589 7064.3741742347 0.0) (10 12750.6989955594
7091.4752369218 0.0) (10 12730.0154977376 7039.9695701357 0.0))
((0 . "LWPOLYLINE") (100 . "AcDbEntity") (8 . "PLANTS") (62 . 94) (370 . 13) (100 . "AcDbPolyline") (90 . 3) (70 . 0)
(43 . 0.0) (10 12692.3076923077 6987.1797511312) (10 12703.4652714932 6979.6314479638) (10 12707.3910633484
6968.3257918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12763.9521493213 252.6385746606 0.0) (10 12747.3291027565 231.0638471137 0.0) (10 12706.1233816883
233.8958773685 0.0) (10 12696.0788461539 260.1809954751 0.0))
((0 . "LWPOLYLINE") (100 . "AcDbEntity") (8 . "PLANTS") (62 . 94) (370 . 13) (100 . "AcDbPolyline") (90 . 3) (70 . 0)
(43 . 0.0) (10 12696.0788461538 260.1809954751) (10 12715.981561086 290.1925339367) (10 12722.4731900452
294.1176470588))
((0 . "LWPOLYLINE") (100 . "AcDbEntity") (8 . "PLANTS") (62 . 94) (370 . 13) (100 . "AcDbPolyline") (90 . 2) (70 . 0)
(43 . 0.0) (10 12699.8487556561 6738.3109728507) (10 12895.92760181 6738.3109728507))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12733.7854072398 6915.5351809955 0.0) (10 12726.4450108183 6925.6937748966 0.0) (10 12732.73956161
6968.3963707702 0.0) (10 12707.3910633484 6968.3257918552 0.0))
((0 . "LWPOLYLINE") (100 . "AcDbEntity") (8 . "PLANTS") (62 . 94) (370 . 13) (100 . "AcDbPolyline") (90 . 3) (70 . 0)
(43 . 0.0) (10 12707.3910633484 6896.6820135747) (10 12707.5458144796 6866.5158371041) (10 12714.9321266968
6847.6618778281))
((0 . "LWPOLYLINE") (100 . "AcDbEntity") (8 . "PLANTS") (62 . 94) (370 . 13) (100 . "AcDbPolyline") (90 . 3) (70 . 0)
(43 . 0.0) (10 12733.7854072398 6907.9942307692) (10 12714.9390271493 6903.0255656109) (10 12707.3910633484
6896.6820135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12714.9321266968 6847.661877828 0.0) (10 12740.1646359458 6825.0348673553 0.0) (10 12784.3866396516
6833.3485023252 0.0) (10 12809.2010180996 6851.4331447963 0.0))
((0 . "LWPOLYLINE") (100 . "AcDbEntity") (8 . "PLANTS") (62 . 94) (370 . 13) (100 . "AcDbPolyline") (90 . 2) (70 . 0)
(43 . 0.0) (10 12722.4731900452 7039.9695701357) (10 12730.0154977376 7039.9695701357))
((0 . "LWPOLYLINE") (100 . "AcDbEntity") (8 . "PLANTS") (62 . 94) (370 . 13) (100 . "AcDbPolyline") (90 . 2) (70 . 0)
(43 . 0.0) (10 12722.4731900452 309.1996606335) (10 12722.4731900452 294.1176470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12722.4731900453 309.1996606334 0.0) (10 12761.4917075115 340.683351376 0.0) (10 12723.080742998
400.2762582735 0.0) (10 12756.409841629 437.4066742081 0.0))
((0 . "LWPOLYLINE") (100 . "AcDbEntity") (8 . "PLANTS") (62 . 94) (370 . 13) (100 . "AcDbPolyline") (90 . 3) (70 . 0)
(43 . 0.0) (10 12763.9521493213 252.6385746606) (10 12737.556561086 282.8054298643) (10 12722.4731900452
294.1176470588))
((0 . "LWPOLYLINE") (100 . "AcDbEntity") (8 . "PLANTS") (62 . 94) (370 . 13) (100 . "AcDbPolyline") (90 . 3) (70 . 0)
(43 . 0.0) (10 12752.6399321267 7013.5746606335) (10 12733.9400452489 7024.893438914) (10 12730.0154977376
7039.9695701357))
((0 . "LWPOLYLINE") (100 . "AcDbEntity") (8 . "PLANTS") (62 . 94) (370 . 13) (100 . "AcDbPolyline") (90 . 2) (70 . 0)
(43 . 0.0) (10 12733.7854072398 6907.9942307692) (10 12733.7854072398 6915.5351809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12733.7854072398 6915.5351809955 0.0) (10 12745.5128733501 6918.1010849204 0.0) (10 12771.1080048607
6917.3057404425 0.0) (10 12775.2643665158 6934.3891402715 0.0))
((0 . "LWPOLYLINE") (100 . "AcDbEntity") (8 . "PLANTS") (62 . 94) (370 . 13) (100 . "AcDbPolyline") (90 . 2) (70 . 0)
(43 . 0.0) (10 12733.7854072398 6907.9942307692) (10 12741.3277149321 6900.4524886878))
((0 . "LWPOLYLINE") (100 . "AcDbEntity") (8 . "PLANTS") (62 . 94) (370 . 13) (100 . "AcDbPolyline") (90 . 3) (70 . 0)
(43 . 0.0) (10 12760.1809954751 6998.4919683258) (10 12753.8372171946 7002.4173076923) (10 12752.6399321267
7013.5746606335))
((0 . "LWPOLYLINE") (100 . "AcDbEntity") (8 . "PLANTS") (62 . 94) (370 . 13) (100 . "AcDbPolyline") (90 . 2) (70 . 0)
(43 . 0.0) (10 12763.9521493213 7032.4286199095) (10 12752.6399321267 7013.5746606335))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12816.742081448 501.5073529412 0.0) (10 12833.3196596256 574.6851004972 0.0) (10 12880.6607618002
637.095530793 0.0) (10 12892.5802746466 711.8628275033 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4072299725)
(40 . 0.533289042) (40 . 1) (40 . 1) (40 . 1) (40 . 1) (10 12788.7881863205 659.0118701112 0.0) (10 12776.3484794615
628.6393416944 0.0) (10 12763.5870200648 591.274948538 0.0) (10 12738.5291716129 517.6973645877 0.0) (10
12731.4659803819 469.536342592 0.0) (10 12756.409841629 437.4066742081 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12816.7420814479 501.5073529412 0.0) (10 12792.0839050854 482.9617326894 0.0) (10 12798.6348301884
438.162467199 0.0) (10 12756.409841629 437.4066742081 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12809.2010180995 7039.9695701357 0.0) (10 12805.046145758 7059.0738129924 0.0) (10 12783.258455867
7075.6489649251 0.0) (10 12763.9521493213 7066.3652714932 0.0))
((0 . "LWPOLYLINE") (100 . "AcDbEntity") (8 . "PLANTS") (62 . 94) (370 . 13) (100 . "AcDbPolyline") (90 . 2) (70 . 0)
(43 . 0.0) (10 12763.9521493213 7039.9695701357) (10 12763.9521493213 7032.4286199095))
((0 . "LWPOLYLINE") (100 . "AcDbEntity") (8 . "PLANTS") (62 . 94) (370 . 13) (100 . "AcDbPolyline") (90 . 2) (70 . 0)
(43 . 0.0) (10 12786.5765837104 7021.1164027149) (10 12763.9521493213 7032.4286199095))
((0 . "LWPOLYLINE") (100 . "AcDbEntity") (8 . "PLANTS") (62 . 94) (370 . 13) (100 . "AcDbPolyline") (90 . 2) (70 . 0)
(43 . 0.0) (10 12763.9521493213 252.6385746606) (10 12790.3464932127 252.6385746606))
((0 . "LWPOLYLINE") (100 . "AcDbEntity") (8 . "PLANTS") (62 . 94) (370 . 13) (100 . "AcDbPolyline") (90 . 3) (70 . 0)
(43 . 0.0) (10 12775.2643665158 6968.3257918552) (10 12769.9701357466 6960.7774886878) (10 12775.2643665158
6934.3891402715))
((0 . "LWPOLYLINE") (100 . "AcDbEntity") (8 . "PLANTS") (62 . 94) (370 . 13) (100 . "AcDbPolyline") (90 . 2) (70 . 0)
(43 . 0.0) (10 12775.2643665158 6934.3891402715) (10 12824.2831447964 6949.4718325792))
((0 . "LWPOLYLINE") (100 . "AcDbEntity") (8 . "PLANTS") (62 . 94) (370 . 13) (100 . "AcDbPolyline") (90 . 2) (70 . 0)
(43 . 0.0) (10 12782.8054298643 305.4298642534) (10 12797.888800905 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12790.3464932127 260.1809954751 0.0) (10 12771.8560219914 265.2338308851 0.0) (10 12767.5741752469
294.5519215269 0.0) (10 12782.8054298643 305.4298642534 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3794715988) (40
. 1) (40 . 1) (40 . 1) (40 . 1) (10 12805.4298642535 384.6153846153 0.0) (10 12801.5692034143 375.1686994139 0.0) (10
12783.0828989805 352.9004754631 0.0) (10 12776.9722553583 324.5543189763 0.0) (10 12782.8054298643 305.4298642534 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12786.5765837104 7021.1164027149 0.0) (10 12779.5252105597 6993.9967899191 0.0) (10 12805.9634964798
6970.551968606 0.0) (10 12824.2831447964 6957.0135746606 0.0))
((0 . "LWPOLYLINE") (100 . "AcDbEntity") (8 . "PLANTS") (62 . 94) (370 . 13) (100 . "AcDbPolyline") (90 . 2) (70 . 0)
(43 . 0.0) (10 12786.5765837104 7021.1164027149) (10 12809.2010180995 7039.9695701357))
((0 . "LWPOLYLINE") (100 . "AcDbEntity") (8 . "PLANTS") (62 . 94) (370 . 13) (100 . "AcDbPolyline") (90 . 2) (70 . 0)
(43 . 0.0) (10 12790.3464932127 260.1809954751) (10 12790.3464932127 252.6385746606))
((0 . "LWPOLYLINE") (100 . "AcDbEntity") (8 . "PLANTS") (62 . 94) (370 . 13) (100 . "AcDbPolyline") (90 . 2) (70 . 0)
(43 . 0.0) (10 12805.4298642534 275.2630090498) (10 12790.3464932127 260.1809954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12929.8642533937 248.8687782805 0.0) (10 12891.5602837422 220.4777911745 0.0) (10 12821.7866509695
212.8396261885 0.0) (10 12790.3464932127 252.6385746606 0.0))
((0 . "LWPOLYLINE") (100 . "AcDbEntity") (8 . "PLANTS") (62 . 94) (370 . 13) (100 . "AcDbPolyline") (90 . 2) (70 . 0)
(43 . 0.0) (10 12805.4298642534 384.6153846154) (10 12794.1176470588 407.2398190045))
((0 . "LWPOLYLINE") (100 . "AcDbEntity") (8 . "PLANTS") (62 . 94) (370 . 13) (100 . "AcDbPolyline") (90 . 3) (70 . 0)
(43 . 0.0) (10 12805.4298642534 275.2630090498) (10 12798.0435520362 286.5752262443) (10 12797.888800905
305.4298642534))
((0 . "LWPOLYLINE") (100 . "AcDbEntity") (8 . "PLANTS") (62 . 94) (370 . 13) (100 . "AcDbPolyline") (90 . 3) (70 . 0)
(43 . 0.0) (10 12843.1376696833 350.6787330317) (10 12828.2020361991 346.7536199095) (10 12797.888800905
305.4298642534))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2956753141)
(40 . 0.4798282553) (40 . 1) (40 . 1) (40 . 1) (40 . 1) (10 12805.4298642535 384.6153846153 0.0) (10 12814.9537776393
391.2272560833 0.0) (10 12823.1732775 406.9195861411 0.0) (10 12851.2170155545 431.8504429901 0.0) (10 12876.6524078592
448.5683307503 0.0) (10 12873.3031674208 471.3433257919 0.0))
((0 . "LWPOLYLINE") (100 . "AcDbEntity") (8 . "PLANTS") (62 . 94) (370 . 13) (100 . "AcDbPolyline") (90 . 2) (70 . 0)
(43 . 0.0) (10 12805.4298642534 275.2630090498) (10 12835.595361991 286.5752262443))
((0 . "LWPOLYLINE") (100 . "AcDbEntity") (8 . "PLANTS") (62 . 94) (370 . 13) (100 . "AcDbPolyline") (90 . 2) (70 . 0)
(43 . 0.0) (10 12835.595361991 7032.4286199095) (10 12809.2010180995 7039.9695701357))
((0 . "LWPOLYLINE") (100 . "AcDbEntity") (8 . "PLANTS") (62 . 94) (370 . 13) (100 . "AcDbPolyline") (90 . 3) (70 . 0)
(43 . 0.0) (10 12835.595361991 6900.4524886878) (10 12814.1694570136 6881.5985294118) (10 12809.2010180995
6851.4331447964))
((0 . "LWPOLYLINE") (100 . "AcDbEntity") (8 . "PLANTS") (62 . 94) (370 . 13) (100 . "AcDbPolyline") (90 . 3) (70 . 0)
(43 . 0.0) (10 12809.2010180995 6851.4331447964) (10 12854.4498868778 6851.5875565611) (10 12865.7621040724
6858.9740950226))
((0 . "LWPOLYLINE") (100 . "AcDbEntity") (8 . "PLANTS") (62 . 94) (370 . 13) (100 . "AcDbPolyline") (90 . 2) (70 . 0)
(43 . 0.0) (10 12812.9709276018 629.7143665158) (10 12820.5132352941 629.7143665158))
((0 . "LWPOLYLINE") (100 . "AcDbEntity") (8 . "PLANTS") (62 . 94) (370 . 13) (100 . "AcDbPolyline") (90 . 2) (70 . 0)
(43 . 0.0) (10 12858.2197963801 501.5073529412) (10 12816.742081448 501.5073529412))
((0 . "LWPOLYLINE") (100 . "AcDbEntity") (8 . "PLANTS") (62 . 94) (370 . 13) (100 . "AcDbPolyline") (90 . 2) (70 . 0)
(43 . 0.0) (10 12824.2831447964 6957.0135746606) (10 12824.2831447964 6949.4718325792))
((0 . "LWPOLYLINE") (100 . "AcDbEntity") (8 . "PLANTS") (62 . 94) (370 . 13) (100 . "AcDbPolyline") (90 . 2) (70 . 0)
(43 . 0.0) (10 12877.074321267 6958.8992081448) (10 12824.2831447964 6957.0135746606))
((0 . "LWPOLYLINE") (100 . "AcDbEntity") (8 . "PLANTS") (62 . 94) (370 . 13) (100 . "AcDbPolyline") (90 . 3) (70 . 0)
(43 . 0.0) (10 12835.595361991 6919.3064479638) (10 12830.628280543 6945.5464932127) (10 12824.2831447964
6949.4718325792))
((0 . "LWPOLYLINE") (100 . "AcDbEntity") (8 . "PLANTS") (62 . 94) (370 . 13) (100 . "AcDbPolyline") (90 . 3) (70 . 0)
(43 . 0.0) (10 12835.595361991 7032.4286199095) (10 12843.1445701357 7017.3520361991) (10 12858.2197963801
7009.8041855204))
((0 . "LWPOLYLINE") (100 . "AcDbEntity") (8 . "PLANTS") (62 . 94) (370 . 13) (100 . "AcDbPolyline") (90 . 2) (70 . 0)
(43 . 0.0) (10 12835.595361991 7032.4286199095) (10 12854.4498868778 7058.8235294118))
((0 . "LWPOLYLINE") (100 . "AcDbEntity") (8 . "PLANTS") (62 . 94) (370 . 13) (100 . "AcDbPolyline") (90 . 2) (70 . 0)
(43 . 0.0) (10 12835.595361991 6900.4524886878) (10 12835.595361991 6919.3064479638))
((0 . "LWPOLYLINE") (100 . "AcDbEntity") (8 . "PLANTS") (62 . 94) (370 . 13) (100 . "AcDbPolyline") (90 . 2) (70 . 0)
(43 . 0.0) (10 12869.5320135747 6923.0769230769) (10 12835.595361991 6919.3064479638))
((0 . "LWPOLYLINE") (100 . "AcDbEntity") (8 . "PLANTS") (62 . 94) (370 . 13) (100 . "AcDbPolyline") (90 . 2) (70 . 0)
(43 . 0.0) (10 12835.595361991 6900.4524886878) (10 12865.7621040724 6858.9740950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12892.1564479638 312.9722850679 0.0) (10 12882.4219095371 305.7211969537 0.0) (10 12855.0395057002
271.5194047837 0.0) (10 12835.595361991 286.5752262443 0.0))
((0 . "LWPOLYLINE") (100 . "AcDbEntity") (8 . "PLANTS") (62 . 94) (370 . 13) (100 . "AcDbPolyline") (90 . 3) (70 . 0)
(43 . 0.0) (10 12858.2197963801 331.8240950226) (10 12840.5636877828 305.4298642534) (10 12835.595361991
286.5752262443))
((0 . "LWPOLYLINE") (100 . "AcDbEntity") (8 . "PLANTS") (62 . 94) (370 . 13) (100 . "AcDbPolyline") (90 . 2) (70 . 0)
(43 . 0.0) (10 12843.1376696833 350.6787330317) (10 12858.2197963801 331.8240950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12843.1376696832 350.6787330317 0.0) (10 12844.8228919542 400.2007172437 0.0) (10 12897.0344455989
429.9452348878 0.0) (10 12933.6354072398 456.2584841629 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12854.4498868778 7058.8235294118 0.0) (10 12885.3401569664 7093.3876333209 0.0) (10 12808.2676308235
7123.3266629417 0.0) (10 12846.9075791855 7149.3212669683 0.0))
((0 . "LWPOLYLINE") (100 . "AcDbEntity") (8 . "PLANTS") (62 . 94) (370 . 13) (100 . "AcDbPolyline") (90 . 3) (70 . 0)
(43 . 0.0) (10 12854.4498868778 7058.8235294118) (10 12877.074321267 7044.9516968326) (10 12888.3865384615
7051.2817873303))
((0 . "LWPOLYLINE") (100 . "AcDbEntity") (8 . "PLANTS") (62 . 94) (370 . 13) (100 . "AcDbPolyline") (90 . 3) (70 . 0)
(43 . 0.0) (10 12858.2197963801 501.5073529412) (10 12859.4238687783 486.4253393665) (10 12873.3031674208
471.3433257919))
((0 . "LWPOLYLINE") (100 . "AcDbEntity") (8 . "PLANTS") (62 . 94) (370 . 13) (100 . "AcDbPolyline") (90 . 2) (70 . 0)
(43 . 0.0) (10 12858.2197963801 501.5073529412) (10 12863.6950880859 509.6665215785))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12970.5285338217 497.7375565611 0.0) (10 12959.7438569932 481.6725888 0.0) (10 12934.415748229
479.8036016063 0.0) (10 12933.6354072398 456.2584841629 0.0))
((0 . "LWPOLYLINE") (100 . "AcDbEntity") (8 . "PLANTS") (62 . 94) (370 . 13) (100 . "AcDbPolyline") (90 . 2) (70 . 0)
(43 . 0.0) (10 12880.8442307692 335.596719457) (10 12858.2197963801 331.8240950226))
((0 . "LWPOLYLINE") (100 . "AcDbEntity") (8 . "PLANTS") (62 . 94) (370 . 13) (100 . "AcDbPolyline") (90 . 2) (70 . 0)
(43 . 0.0) (10 12877.074321267 6858.9740950226) (10 12865.7621040724 6858.9740950226))
((0 . "LWPOLYLINE") (100 . "AcDbEntity") (8 . "PLANTS") (62 . 94) (370 . 13) (100 . "AcDbPolyline") (90 . 2) (70 . 0)
(43 . 0.0) (10 12869.5320135747 6923.0769230769) (10 12888.3865384615 6904.2229638009))
((0 . "LWPOLYLINE") (100 . "AcDbEntity") (8 . "PLANTS") (62 . 94) (370 . 13) (100 . "AcDbPolyline") (90 . 2) (70 . 0)
(43 . 0.0) (10 12869.5320135747 6923.0769230769) (10 12877.074321267 6958.8992081448))
((0 . "LWPOLYLINE") (100 . "AcDbEntity") (8 . "PLANTS") (62 . 94) (370 . 13) (100 . "AcDbPolyline") (90 . 3) (70 . 0)
(43 . 0.0) (10 12910.3710124194 497.7375565611) (10 12888.2374434389 476.1694570136) (10 12873.3031674208
471.3433257919))
((0 . "LWPOLYLINE") (100 . "AcDbEntity") (8 . "PLANTS") (62 . 94) (370 . 13) (100 . "AcDbPolyline") (90 . 3) (70 . 0)
(43 . 0.0) (10 12877.074321267 6958.8992081448) (10 12885.671719457 6983.4084841629) (10 12922.3231900453
7021.1164027149))
((0 . "LWPOLYLINE") (100 . "AcDbEntity") (8 . "PLANTS") (62 . 94) (370 . 13) (100 . "AcDbPolyline") (90 . 2) (70 . 0)
(43 . 0.0) (10 12922.3231900453 6960.7840497738) (10 12877.074321267 6958.8992081448))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5644511685) (40
. 1) (40 . 1) (40 . 1) (40 . 1) (10 12877.0743212669 6858.9740950227 0.0) (10 12891.0541118292 6840.1460847017 0.0) (10
12925.2380814963 6849.1823925358 0.0) (10 12942.7700377761 6880.4607289127 0.0) (10 12956.2598416289 6881.5985294118
0.0))
((0 . "LWPOLYLINE") (100 . "AcDbEntity") (8 . "PLANTS") (62 . 94) (370 . 13) (100 . "AcDbPolyline") (90 . 3) (70 . 0)
(43 . 0.0) (10 12877.074321267 6858.9740950226) (10 12887.3371040724 6885.3697963801) (10 12888.3865384615
6904.2229638009))
((0 . "LWPOLYLINE") (100 . "AcDbEntity") (8 . "PLANTS") (62 . 94) (370 . 13) (100 . "AcDbPolyline") (90 . 2) (70 . 0)
(43 . 0.0) (10 12892.1564479638 312.9722850679) (10 12880.8442307692 335.596719457))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7055636085) (40
. 1) (40 . 1) (40 . 1) (40 . 1) (10 12880.8442307692 335.596719457 0.0) (10 12892.3938846907 375.5333720728 0.0) (10
12942.6047099365 359.3806952741 0.0) (10 12971.102031125 388.6739859623 0.0) (10 12982.6541855203 392.1578054299 0.0))
((0 . "LWPOLYLINE") (100 . "AcDbEntity") (8 . "PLANTS") (62 . 94) (370 . 13) (100 . "AcDbPolyline") (90 . 3) (70 . 0)
(43 . 0.0) (10 12920.4369909502 296.003959276) (10 12895.92760181 276.3201357466) (10 12880.8442307692 271.4932126697))
((0 . "LWPOLYLINE") (100 . "AcDbEntity") (8 . "PLANTS") (62 . 94) (370 . 13) (100 . "AcDbPolyline") (90 . 2) (70 . 0)
(43 . 0.0) (10 12903.4686651584 6904.2229638009) (10 12888.3865384615 6904.2229638009))
((0 . "LWPOLYLINE") (100 . "AcDbEntity") (8 . "PLANTS") (62 . 94) (370 . 13) (100 . "AcDbPolyline") (90 . 3) (70 . 0)
(43 . 0.0) (10 12920.4369909502 296.003959276) (10 12903.4686651584 311.7667420814) (10 12892.1564479638
312.9722850679))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12903.4686651584 6904.2229638009 0.0) (10 12917.5849395128 6891.0580806337 0.0) (10 12934.7904755054
6914.9254727887 0.0) (10 12933.6354072398 6926.84739819 0.0))
((0 . "LWPOLYLINE") (100 . "AcDbEntity") (8 . "PLANTS") (62 . 94) (370 . 13) (100 . "AcDbPolyline") (90 . 3) (70 . 0)
(43 . 0.0) (10 12903.4686651584 6904.2229638009) (10 12912.2082579186 6923.070361991) (10 12922.3231900453
6930.6186651584))
((0 . "LWPOLYLINE") (100 . "AcDbEntity") (8 . "PLANTS") (62 . 94) (370 . 13) (100 . "AcDbPolyline") (90 . 3) (70 . 0)
(43 . 0.0) (10 12920.4369909502 296.003959276) (10 12925.8707013575 286.6435520362) (10 12929.8642533937
248.8687782805))
((0 . "LWPOLYLINE") (100 . "AcDbEntity") (8 . "PLANTS") (62 . 94) (370 . 13) (100 . "AcDbPolyline") (90 . 3) (70 . 0)
(43 . 0.0) (10 12920.4369909502 296.003959276) (10 12926.0930995475 305.4298642534) (10 12929.8642533937
305.4298642534))
((0 . "LWPOLYLINE") (100 . "AcDbEntity") (8 . "PLANTS") (62 . 94) (370 . 13) (100 . "AcDbPolyline") (90 . 2) (70 . 0)
(43 . 0.0) (10 12922.3231900453 6960.7840497738) (10 12922.3231900453 6930.6186651584))
((0 . "LWPOLYLINE") (100 . "AcDbEntity") (8 . "PLANTS") (62 . 94) (370 . 13) (100 . "AcDbPolyline") (90 . 3) (70 . 0)
(43 . 0.0) (10 12922.3231900453 6960.7840497738) (10 12930.0119909502 6971.9421945701) (10 12941.1764705882
6975.8675339367))
((0 . "LWPOLYLINE") (100 . "AcDbEntity") (8 . "PLANTS") (62 . 94) (370 . 13) (100 . "AcDbPolyline") (90 . 2) (70 . 0)
(43 . 0.0) (10 12933.6354072398 6926.84739819) (10 12922.3231900453 6930.6186651584))
((0 . "LWPOLYLINE") (100 . "AcDbEntity") (8 . "PLANTS") (62 . 94) (370 . 13) (100 . "AcDbPolyline") (90 . 3) (70 . 0)
(43 . 0.0) (10 12929.8642533937 305.4298642534) (10 12956.259841629 305.2821266968) (10 13031.6742081448
282.8054298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12929.8642533937 305.4298642534 0.0) (10 12926.9063164447 339.9587774162 0.0) (10 12966.5640487185
362.2445294988 0.0) (10 12997.7375565611 346.9089366516 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13009.0497737557 237.556561086 0.0) (10 12983.4817877396 226.7658674695 0.0) (10 12951.9725303892
232.7924518908 0.0) (10 12929.8642533937 248.8687782805 0.0))
((0 . "LWPOLYLINE") (100 . "AcDbEntity") (8 . "PLANTS") (62 . 94) (370 . 13) (100 . "AcDbPolyline") (90 . 3) (70 . 0)
(43 . 0.0) (10 12933.6354072398 7051.2817873303) (10 12934.6918552036 7036.1990950226) (10 12952.4886877828
7006.032918552))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5565307445) (40
. 1) (40 . 1) (40 . 1) (40 . 1) (10 12933.6354072399 7051.2817873303 0.0) (10 12908.7463398272 7066.4634822569 0.0) (10
12945.2078221017 7125.3853683985 0.0) (10 12982.2016226386 7096.8080090864 0.0) (10 12971.3419683258 7066.3652714932
0.0))
((0 . "LWPOLYLINE") (100 . "AcDbEntity") (8 . "PLANTS") (62 . 94) (370 . 13) (100 . "AcDbPolyline") (90 . 2) (70 . 0)
(43 . 0.0) (10 12933.6354072398 7051.2817873303) (10 12971.3419683258 7066.3652714932))
((0 . "LWPOLYLINE") (100 . "AcDbEntity") (8 . "PLANTS") (62 . 94) (370 . 13) (100 . "AcDbPolyline") (90 . 3) (70 . 0)
(43 . 0.0) (10 12963.8009049774 6949.4718325792) (10 12944.9476244344 6930.7730769231) (10 12933.6354072398
6926.84739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12982.6541855204 399.69739819 0.0) (10 12980.9347419462 426.6340788676 0.0) (10 12957.4950186606
447.5056142554 0.0) (10 12933.6354072398 456.2584841629 0.0))
((0 . "LWPOLYLINE") (100 . "AcDbEntity") (8 . "PLANTS") (62 . 94) (370 . 13) (100 . "AcDbPolyline") (90 . 2) (70 . 0)
(43 . 0.0) (10 12944.9476244344 6779.7885746606) (10 12937.4053167421 6779.7885746606))
((0 . "LWPOLYLINE") (100 . "AcDbEntity") (8 . "PLANTS") (62 . 94) (370 . 13) (100 . "AcDbPolyline") (90 . 3) (70 . 0)
(43 . 0.0) (10 12937.4053167421 6779.7885746606) (10 12937.5599547511 6749.6231900452) (10 12948.7175339367
6734.5397058824))
((0 . "LWPOLYLINE") (100 . "AcDbEntity") (8 . "PLANTS") (62 . 94) (370 . 13) (100 . "AcDbPolyline") (90 . 3) (70 . 0)
(43 . 0.0) (10 12963.8009049774 6949.4718325792) (10 12952.3409502262 6968.1774886878) (10 12941.1764705882
6975.8675339367))
((0 . "LWPOLYLINE") (100 . "AcDbEntity") (8 . "PLANTS") (62 . 94) (370 . 13) (100 . "AcDbPolyline") (90 . 3) (70 . 0)
(43 . 0.0) (10 12941.1764705882 6975.8675339367) (10 12946.0040723982 6998.4850678733) (10 12952.4886877828
7006.032918552))
((0 . "LWPOLYLINE") (100 . "AcDbEntity") (8 . "PLANTS") (62 . 94) (370 . 13) (100 . "AcDbPolyline") (90 . 2) (70 . 0)
(43 . 0.0) (10 12944.9476244344 6553.5442307692) (10 12943.4129987579 6548.9408601105))
((0 . "LWPOLYLINE") (100 . "AcDbEntity") (8 . "PLANTS") (62 . 94) (370 . 13) (100 . "AcDbPolyline") (90 . 2) (70 . 0)
(43 . 0.0) (10 12944.9476244344 6779.7885746606) (10 13042.9864253394 6779.7885746606))
((0 . "LWPOLYLINE") (100 . "AcDbEntity") (8 . "PLANTS") (62 . 94) (370 . 13) (100 . "AcDbPolyline") (90 . 3) (70 . 0)
(43 . 0.0) (10 12944.9476244344 6779.7885746606) (10 12945.0954751131 6825.0374434389) (10 12960.0297511312
6858.9740950226))
((0 . "LWPOLYLINE") (100 . "AcDbEntity") (8 . "PLANTS") (62 . 94) (370 . 13) (100 . "AcDbPolyline") (90 . 3) (70 . 0)
(43 . 0.0) (10 12956.259841629 6636.5010180995) (10 12948.7175339367 6640.2714932127) (10 12944.9476244344
6647.8132352941))
((0 . "LWPOLYLINE") (100 . "AcDbEntity") (8 . "PLANTS") (62 . 94) (370 . 13) (100 . "AcDbPolyline") (90 . 3) (70 . 0)
(43 . 0.0) (10 12944.9476244344 6553.5442307692) (10 12941.1764705882 6568.6277149321) (10 12944.9476244344
6591.2521493213))
((0 . "LWPOLYLINE") (100 . "AcDbEntity") (8 . "PLANTS") (62 . 94) (370 . 13) (100 . "AcDbPolyline") (90 . 2) (70 . 0)
(43 . 0.0) (10 12944.9476244344 6553.5442307692) (10 12960.0297511312 6564.8564479638))
((0 . "LWPOLYLINE") (100 . "AcDbEntity") (8 . "PLANTS") (62 . 94) (370 . 13) (100 . "AcDbPolyline") (90 . 3) (70 . 0)
(43 . 0.0) (10 13090.6371087331 3793.6995335291) (10 13099.5475113122 3793.3701357466) (10 13118.4007918552
3797.1338235294))
((0 . "LWPOLYLINE") (100 . "AcDbEntity") (8 . "PLANTS") (62 . 94) (370 . 13) (100 . "AcDbPolyline") (90 . 2) (70 . 0)
(43 . 0.0) (10 12952.4886877828 7006.032918552) (10 12978.8842760181 7002.2624434389))
((0 . "LWPOLYLINE") (100 . "AcDbEntity") (8 . "PLANTS") (62 . 94) (370 . 13) (100 . "AcDbPolyline") (90 . 2) (70 . 0)
(43 . 0.0) (10 12956.259841629 6881.5985294118) (10 12960.0297511312 6858.9740950226))
((0 . "LWPOLYLINE") (100 . "AcDbEntity") (8 . "PLANTS") (62 . 94) (370 . 13) (100 . "AcDbPolyline") (90 . 3) (70 . 0)
(43 . 0.0) (10 12956.259841629 6881.5985294118) (10 12963.8078054299 6892.7632352941) (10 13005.2786199095
6919.3064479638))
((0 . "LWPOLYLINE") (100 . "AcDbEntity") (8 . "PLANTS") (62 . 94) (370 . 13) (100 . "AcDbPolyline") (90 . 3) (70 . 0)
(43 . 0.0) (10 13020.3619909502 6862.745361991) (10 12990.1964932127 6855.3519230769) (10 12960.0297511312
6858.9740950226))
((0 . "LWPOLYLINE") (100 . "AcDbEntity") (8 . "PLANTS") (62 . 94) (370 . 13) (100 . "AcDbPolyline") (90 . 2) (70 . 0)
(43 . 0.0) (10 12993.9664027149 6949.4718325792) (10 12963.8009049774 6949.4718325792))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5795399531) (40
. 1) (40 . 1) (40 . 1) (40 . 1) (10 12967.5720588236 6576.1686651583 0.0) (10 12976.0393458717 6589.8731240726 0.0) (10
12969.8868850318 6621.6915844276 0.0) (10 12998.9907245574 6634.0617643233 0.0) (10 13005.2786199096 6644.0419683257
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12971.3419683258 7066.3652714932 0.0) (10 12995.7676769302 7054.8517726803 0.0) (10 13000.8288070226
7016.6300724394 0.0) (10 12978.8842760181 7002.2624434389 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12971.3419683258 6659.1254524887 0.0) (10 13000.6569424492 6673.6182271346 0.0) (10 12969.47526445
6713.632261903 0.0) (10 13001.5087104072 6723.2274886878 0.0))
((0 . "LWPOLYLINE") (100 . "AcDbEntity") (8 . "PLANTS") (62 . 94) (370 . 13) (100 . "AcDbPolyline") (90 . 3) (70 . 0)
(43 . 0.0) (10 12993.9664027149 6949.4718325792) (10 12983.710520362 6968.3257918552) (10 12978.8842760181
7002.2624434389))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12982.6541855204 399.69739819 0.0) (10 13022.7186100738 415.4447168924 0.0) (10 13019.0742785861
361.2063252825 0.0) (10 13046.7575791855 350.6787330317 0.0))
((0 . "LWPOLYLINE") (100 . "AcDbEntity") (8 . "PLANTS") (62 . 94) (370 . 13) (100 . "AcDbPolyline") (90 . 2) (70 . 0)
(43 . 0.0) (10 12982.6541855204 399.69739819) (10 12982.6541855204 392.1578054299))
((0 . "LWPOLYLINE") (100 . "AcDbEntity") (8 . "PLANTS") (62 . 94) (370 . 13) (100 . "AcDbPolyline") (90 . 2) (70 . 0)
(43 . 0.0) (10 12997.7375565611 346.9089366516) (10 12982.6541855204 392.1578054299))
((0 . "LWPOLYLINE") (100 . "AcDbEntity") (8 . "PLANTS") (62 . 94) (370 . 13) (100 . "AcDbPolyline") (90 . 2) (70 . 0)
(43 . 0.0) (10 12993.9664027149 6949.4718325792) (10 13005.2786199095 6949.4718325792))
((0 . "LWPOLYLINE") (100 . "AcDbEntity") (8 . "PLANTS") (62 . 94) (370 . 13) (100 . "AcDbPolyline") (90 . 2) (70 . 0)
(43 . 0.0) (10 12993.9664027149 471.3433257919) (10 13027.9030542986 444.9462669683))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 12997.7375565611 346.9089366516 0.0) (10 13008.7687404191 336.8660482404 0.0) (10 13044.788924498
306.5567676652 0.0) (10 13031.6742081448 282.8054298643 0.0))
((0 . "LWPOLYLINE") (100 . "AcDbEntity") (8 . "PLANTS") (62 . 94) (370 . 13) (100 . "AcDbPolyline") (90 . 2) (70 . 0)
(43 . 0.0) (10 13005.2786199095 6949.4718325792) (10 13005.2786199095 6919.3064479638))
((0 . "LWPOLYLINE") (100 . "AcDbEntity") (8 . "PLANTS") (62 . 94) (370 . 13) (100 . "AcDbPolyline") (90 . 2) (70 . 0)
(43 . 0.0) (10 13020.3619909502 6957.0135746606) (10 13005.2786199095 6949.4718325792))
((0 . "LWPOLYLINE") (100 . "AcDbEntity") (8 . "PLANTS") (62 . 94) (370 . 13) (100 . "AcDbPolyline") (90 . 2) (70 . 0)
(43 . 0.0) (10 13012.8209276018 6911.7647058824) (10 13005.2786199095 6919.3064479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13084.4641402715 252.6385746606 0.0) (10 13069.2236585037 227.7500309446 0.0) (10 13032.8222143863
223.790421815 0.0) (10 13009.0497737557 237.556561086 0.0))
((0 . "LWPOLYLINE") (100 . "AcDbEntity") (8 . "PLANTS") (62 . 94) (370 . 13) (100 . "AcDbPolyline") (90 . 3) (70 . 0)
(43 . 0.0) (10 13012.8209276018 252.6385746606) (10 13009.0497737557 248.8687782805) (10 13009.0497737557
237.556561086))
((0 . "LWPOLYLINE") (100 . "AcDbEntity") (8 . "PLANTS") (62 . 94) (370 . 13) (100 . "AcDbPolyline") (90 . 3) (70 . 0)
(43 . 0.0) (10 13012.8209276018 6911.7647058824) (10 13020.2142533937 6881.5985294118) (10 13020.3619909502
6862.745361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13012.8209276018 6911.7647058824 0.0) (10 13054.7728467282 6894.6588817847 0.0) (10 13072.2414798805
6949.29659285 0.0) (10 13110.8597285068 6945.7013574661 0.0))
((0 . "LWPOLYLINE") (100 . "AcDbEntity") (8 . "PLANTS") (62 . 94) (370 . 13) (100 . "AcDbPolyline") (90 . 2) (70 . 0)
(43 . 0.0) (10 13020.3619909502 6957.0135746606) (10 13027.9030542986 6998.4919683258))
((0 . "LWPOLYLINE") (100 . "AcDbEntity") (8 . "PLANTS") (62 . 94) (370 . 13) (100 . "AcDbPolyline") (90 . 2) (70 . 0)
(43 . 0.0) (10 13020.3619909502 6957.0135746606) (10 13042.9864253394 6964.5553167421))
((0 . "LWPOLYLINE") (100 . "AcDbEntity") (8 . "PLANTS") (62 . 94) (370 . 13) (100 . "AcDbPolyline") (90 . 3) (70 . 0)
(43 . 0.0) (10 13020.3619909502 6862.745361991) (10 13035.5131221719 6862.5229638009) (10 13044.8713800905
6857.0892533937))
((0 . "LWPOLYLINE") (100 . "AcDbEntity") (8 . "PLANTS") (62 . 94) (370 . 13) (100 . "AcDbPolyline") (90 . 2) (70 . 0)
(43 . 0.0) (10 13027.9030542986 7036.1990950226) (10 13050.5274886878 7028.6573529412))
((0 . "LWPOLYLINE") (100 . "AcDbEntity") (8 . "PLANTS") (62 . 94) (370 . 13) (100 . "AcDbPolyline") (90 . 3) (70 . 0)
(43 . 0.0) (10 13027.9030542986 6998.4919683258) (10 13024.1331447964 7013.5746606335) (10 13027.9030542986
7036.1990950226))
((0 . "LWPOLYLINE") (100 . "AcDbEntity") (8 . "PLANTS") (62 . 94) (370 . 13) (100 . "AcDbPolyline") (90 . 3) (70 . 0)
(43 . 0.0) (10 13050.5274886878 7081.4479638009) (10 13029.1071266968 7062.5940045249) (10 13027.9030542986
7036.1990950226))
((0 . "LWPOLYLINE") (100 . "AcDbEntity") (8 . "PLANTS") (62 . 94) (370 . 13) (100 . "AcDbPolyline") (90 . 2) (70 . 0)
(43 . 0.0) (10 13027.9030542986 6998.4919683258) (10 13050.5274886878 7017.3451357466))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13027.9030542986 444.9462669683 0.0) (10 13022.9532344806 409.6437865533 0.0) (10 13071.378644358
391.0027346728 0.0) (10 13061.8397058824 354.4485294118 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6222988998) (40
. 1) (40 . 1) (40 . 1) (40 . 1) (10 13137.2553167421 388.3851809955 0.0) (10 13137.4847080931 408.5850475542 0.0) (10
13099.7685288828 510.7352593342 0.0) (10 13048.7565256289 442.4755963314 0.0) (10 13027.9030542987 444.9462669683 0.0))
((0 . "LWPOLYLINE") (100 . "AcDbEntity") (8 . "PLANTS") (62 . 94) (370 . 13) (100 . "AcDbPolyline") (90 . 2) (70 . 0)
(43 . 0.0) (10 13039.2152714932 6715.6865384615) (10 13031.6742081448 6734.5397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13031.6742081448 6440.42239819 0.0) (10 13024.3046934305 6440.4951556408 0.0) (10 13027.6618375341
6417.5671312726 0.0) (10 13035.445361991 6425.3393665158 0.0))
((0 . "LWPOLYLINE") (100 . "AcDbEntity") (8 . "PLANTS") (62 . 94) (370 . 13) (100 . "AcDbPolyline") (90 . 3) (70 . 0)
(43 . 0.0) (10 13084.4641402715 252.6385746606) (10 13073.1519230769 262.8951357466) (10 13031.6742081448
282.8054298643))
((0 . "LWPOLYLINE") (100 . "AcDbEntity") (8 . "PLANTS") (62 . 94) (370 . 13) (100 . "AcDbPolyline") (90 . 3) (70 . 0)
(43 . 0.0) (10 13035.445361991 6515.8371040724) (10 13042.9864253394 6527.149321267) (10 13046.7575791855
6527.149321267))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5288157896) (40
. 1) (40 . 1) (40 . 1) (40 . 1) (10 13073.1519230769 6708.1447963802 0.0) (10 13077.6776336931 6688.3226086968 0.0) (10
13045.0871526293 6673.829688576 0.0) (10 13026.6048596042 6698.0191929126 0.0) (10 13039.2152714932 6715.6865384616
0.0))
((0 . "LWPOLYLINE") (100 . "AcDbEntity") (8 . "PLANTS") (62 . 94) (370 . 13) (100 . "AcDbPolyline") (90 . 2) (70 . 0)
(43 . 0.0) (10 13039.2152714932 6715.6865384615) (10 13065.6108597285 6725.1131221719))
((0 . "LWPOLYLINE") (100 . "AcDbEntity") (8 . "PLANTS") (62 . 94) (370 . 13) (100 . "AcDbPolyline") (90 . 2) (70 . 0)
(43 . 0.0) (10 13058.0697963801 6779.7885746606) (10 13042.9864253394 6779.7885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13065.6108597285 6745.8519230769 0.0) (10 13049.2976185693 6745.5613510402 0.0) (10 13034.0831293116
6762.5575574218 0.0) (10 13042.9864253394 6779.7885746606 0.0))
((0 . "LWPOLYLINE") (100 . "AcDbEntity") (8 . "PLANTS") (62 . 94) (370 . 13) (100 . "AcDbPolyline") (90 . 3) (70 . 0)
(43 . 0.0) (10 13046.7575791855 6847.6618778281) (10 13050.5274886878 6851.4331447964) (10 13044.8713800905
6857.0892533937))
((0 . "LWPOLYLINE") (100 . "AcDbEntity") (8 . "PLANTS") (62 . 94) (370 . 13) (100 . "AcDbPolyline") (90 . 2) (70 . 0)
(43 . 0.0) (10 13044.8713800905 6857.0892533937) (10 13046.7575791855 6847.6618778281))
((0 . "LWPOLYLINE") (100 . "AcDbEntity") (8 . "PLANTS") (62 . 94) (370 . 13) (100 . "AcDbPolyline") (90 . 3) (70 . 0)
(43 . 0.0) (10 13046.7575791855 6847.6618778281) (10 13042.9864253394 6851.4331447964) (10 13044.8713800905
6857.0892533937))
((0 . "LWPOLYLINE") (100 . "AcDbEntity") (8 . "PLANTS") (62 . 94) (370 . 13) (100 . "AcDbPolyline") (90 . 3) (70 . 0)
(43 . 0.0) (10 13044.8713800905 6857.0892533937) (10 13061.8397058824 6869.088800905) (10 13080.6942307692
6870.2863122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13046.7575791855 6847.6618778281 0.0) (10 13043.191765021 6823.3569599646 0.0) (10 13068.1811643068
6805.0787134966 0.0) (10 13058.0697963801 6779.7885746606 0.0))
((0 . "LWPOLYLINE") (100 . "AcDbEntity") (8 . "PLANTS") (62 . 94) (370 . 13) (100 . "AcDbPolyline") (90 . 2) (70 . 0)
(43 . 0.0) (10 13046.7575791855 6527.149321267) (10 13046.7575791855 6534.6910633484))
((0 . "LWPOLYLINE") (100 . "AcDbEntity") (8 . "PLANTS") (62 . 94) (370 . 13) (100 . "AcDbPolyline") (90 . 2) (70 . 0)
(43 . 0.0) (10 13046.7575791855 6527.149321267) (10 13076.9230769231 6519.6075791855))
((0 . "LWPOLYLINE") (100 . "AcDbEntity") (8 . "PLANTS") (62 . 94) (370 . 13) (100 . "AcDbPolyline") (90 . 3) (70 . 0)
(43 . 0.0) (10 13046.7575791855 350.6787330317) (10 13058.0697963801 350.6787330317) (10 13061.8397058824
354.4485294118))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13076.9230769231 324.2845022624 0.0) (10 13062.0042445958 322.3358622231 0.0) (10 13046.0837412787
334.2393689746 0.0) (10 13046.7575791855 350.6787330317 0.0))
((0 . "LWPOLYLINE") (100 . "AcDbEntity") (8 . "PLANTS") (62 . 94) (370 . 13) (100 . "AcDbPolyline") (90 . 2) (70 . 0)
(43 . 0.0) (10 13050.5274886878 7017.3451357466) (10 13050.5274886878 7028.6573529412))
((0 . "LWPOLYLINE") (100 . "AcDbEntity") (8 . "PLANTS") (62 . 94) (370 . 13) (100 . "AcDbPolyline") (90 . 2) (70 . 0)
(43 . 0.0) (10 13084.4641402715 7058.8235294118) (10 13050.5274886878 7028.6573529412))
((0 . "LWPOLYLINE") (100 . "AcDbEntity") (8 . "PLANTS") (62 . 94) (370 . 13) (100 . "AcDbPolyline") (90 . 3) (70 . 0)
(43 . 0.0) (10 13050.5274886878 7017.3451357466) (10 13061.8341628959 7009.7976244344) (10 13069.3820135747
6998.4919683258))
((0 . "LWPOLYLINE") (100 . "AcDbEntity") (8 . "PLANTS") (62 . 94) (370 . 13) (100 . "AcDbPolyline") (90 . 2) (70 . 0)
(43 . 0.0) (10 13058.0697963801 6979.6380090498) (10 13069.3820135747 6998.4919683258))
((0 . "LWPOLYLINE") (100 . "AcDbEntity") (8 . "PLANTS") (62 . 94) (370 . 13) (100 . "AcDbPolyline") (90 . 3) (70 . 0)
(43 . 0.0) (10 13078.8080316742 6774.1324660633) (10 13069.4497737557 6779.5668552036) (10 13058.0697963801
6779.7885746606))
((0 . "LWPOLYLINE") (100 . "AcDbEntity") (8 . "PLANTS") (62 . 94) (370 . 13) (100 . "AcDbPolyline") (90 . 3) (70 . 0)
(43 . 0.0) (10 13076.9230769231 324.2845022624) (10 13071.9477375566 346.9013574661) (10 13061.8397058824
354.4485294118))
((0 . "LWPOLYLINE") (100 . "AcDbEntity") (8 . "PLANTS") (62 . 94) (370 . 13) (100 . "AcDbPolyline") (90 . 2) (70 . 0)
(43 . 0.0) (10 13065.6108597285 6745.8519230769) (10 13065.6108597285 6725.1131221719))
((0 . "LWPOLYLINE") (100 . "AcDbEntity") (8 . "PLANTS") (62 . 94) (370 . 13) (100 . "AcDbPolyline") (90 . 3) (70 . 0)
(43 . 0.0) (10 13078.8080316742 6774.1324660633) (10 13073.2264705882 6768.3959276018) (10 13065.6108597285
6745.8519230769))
((0 . "LWPOLYLINE") (100 . "AcDbEntity") (8 . "PLANTS") (62 . 94) (370 . 13) (100 . "AcDbPolyline") (90 . 2) (70 . 0)
(43 . 0.0) (10 13073.1519230769 6708.1447963801) (10 13065.6108597285 6725.1131221719))
((0 . "LWPOLYLINE") (100 . "AcDbEntity") (8 . "PLANTS") (62 . 94) (370 . 13) (100 . "AcDbPolyline") (90 . 2) (70 . 0)
(43 . 0.0) (10 13065.6108597285 6725.1131221719) (10 13088.2352941176 6726.9987556561))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13069.3820135747 6312.2171945701 0.0) (10 13054.3661934513 6308.3729773707 0.0) (10 13045.8649699731
6278.465173182 0.0) (10 13065.6108597285 6274.5097285068 0.0))
((0 . "LWPOLYLINE") (100 . "AcDbEntity") (8 . "PLANTS") (62 . 94) (370 . 13) (100 . "AcDbPolyline") (90 . 2) (70 . 0)
(43 . 0.0) (10 13069.3820135747 6998.4919683258) (10 13084.4641402715 6998.4919683258))
((0 . "LWPOLYLINE") (100 . "AcDbEntity") (8 . "PLANTS") (62 . 94) (370 . 13) (100 . "AcDbPolyline") (90 . 2) (70 . 0)
(43 . 0.0) (10 13069.3820135747 6610.1053167421) (10 13069.3820135747 6576.1686651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13076.9230769231 6640.2714932127 0.0) (10 13049.1652277587 6652.0468223028 0.0) (10 13033.7615156329
6600.6290161943 0.0) (10 13069.3820135747 6610.1053167421 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13076.9230769231 6640.2714932127 0.0) (10 13090.4775414761 6632.4404772937 0.0) (10 13085.6004834511
6608.0547888122 0.0) (10 13069.3820135747 6610.1053167421 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13069.3820135747 6576.1686651584 0.0) (10 13058.0215602738 6554.1102080628 0.0) (10 13086.2082707552
6541.1951751676 0.0) (10 13076.9230769231 6519.6075791855 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13122.1719457014 6553.5442307692 0.0) (10 13109.7360925194 6566.6779861838 0.0) (10 13090.5408726208
6588.0224383118 0.0) (10 13069.3820135747 6576.1686651584 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13069.3820135747 6478.129638009 0.0) (10 13036.4323939949 6409.9556129922 0.0) (10 13121.2140925924
6454.82084392 0.0) (10 13118.4007918552 6402.7149321267 0.0))
((0 . "LWPOLYLINE") (100 . "AcDbEntity") (8 . "PLANTS") (62 . 94) (370 . 13) (100 . "AcDbPolyline") (90 . 2) (70 . 0)
(43 . 0.0) (10 13069.3820135747 6478.129638009) (10 13080.6942307692 6481.9004524887))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7366641474) (40
. 1) (40 . 1) (40 . 1) (40 . 1) (10 13069.3820135747 6312.2171945701 0.0) (10 13076.0653264107 6337.0176276626 0.0) (10
13072.7776303641 6372.1466717984 0.0) (10 13070.2062905164 6405.4406028062 0.0) (10 13069.3820135748 6414.0271493213
0.0))
((0 . "LWPOLYLINE") (100 . "AcDbEntity") (8 . "PLANTS") (62 . 94) (370 . 13) (100 . "AcDbPolyline") (90 . 3) (70 . 0)
(43 . 0.0) (10 13069.3820135747 6312.2171945701) (10 13083.4021493213 6300.8984162896) (10 13084.4641402715
6285.8219457014))
((0 . "LWPOLYLINE") (100 . "AcDbEntity") (8 . "PLANTS") (62 . 94) (370 . 13) (100 . "AcDbPolyline") (90 . 3) (70 . 0)
(43 . 0.0) (10 13073.1519230769 6708.1447963801) (10 13087.0311085973 6715.8340497738) (10 13088.2352941176
6726.9987556561))
((0 . "LWPOLYLINE") (100 . "AcDbEntity") (8 . "PLANTS") (62 . 94) (370 . 13) (100 . "AcDbPolyline") (90 . 2) (70 . 0)
(43 . 0.0) (10 13080.6942307692 6659.1254524887) (10 13076.9230769231 6640.2714932127))
((0 . "LWPOLYLINE") (100 . "AcDbEntity") (8 . "PLANTS") (62 . 94) (370 . 13) (100 . "AcDbPolyline") (90 . 2) (70 . 0)
(43 . 0.0) (10 13076.9230769231 6519.6075791855) (10 13080.6942307692 6481.9004524887))
((0 . "LWPOLYLINE") (100 . "AcDbEntity") (8 . "PLANTS") (62 . 94) (370 . 13) (100 . "AcDbPolyline") (90 . 2) (70 . 0)
(43 . 0.0) (10 13099.5475113122 369.5333710407) (10 13076.9230769231 418.5520361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13076.9230769231 324.2845022624 0.0) (10 13103.4607517746 310.5149162455 0.0) (10 13088.3211278905
275.7865599922 0.0) (10 13112.7446832579 262.0673076923 0.0))
((0 . "LWPOLYLINE") (100 . "AcDbEntity") (8 . "PLANTS") (62 . 94) (370 . 13) (100 . "AcDbPolyline") (90 . 3) (70 . 0)
(43 . 0.0) (10 13078.8080316742 6774.1324660633) (10 13086.9634615385 6764.7734162896) (10 13095.7763574661
6734.5397058824))
((0 . "LWPOLYLINE") (100 . "AcDbEntity") (8 . "PLANTS") (62 . 94) (370 . 13) (100 . "AcDbPolyline") (90 . 2) (70 . 0)
(43 . 0.0) (10 13078.8080316742 6774.1324660633) (10 13099.5475113122 6783.559841629))
((0 . "LWPOLYLINE") (100 . "AcDbEntity") (8 . "PLANTS") (62 . 94) (370 . 13) (100 . "AcDbPolyline") (90 . 3) (70 . 0)
(43 . 0.0) (10 13103.3186651584 6855.2036199095) (10 13088.3830316742 6860.1718325792) (10 13080.6942307692
6870.2863122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13118.4007918552 6881.5985294118 0.0) (10 13110.4664889561 6899.2291990712 0.0) (10 13081.8858740662
6885.9574734451 0.0) (10 13080.6942307692 6870.2863122172 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13080.6942307692 6481.9004524887 0.0) (10 13105.2933944527 6471.059749884 0.0) (10 13131.2246793532
6487.9469642041 0.0) (10 13156.0708647035 6479.3971591619 0.0))
((0 . "LWPOLYLINE") (100 . "AcDbEntity") (8 . "PLANTS") (62 . 94) (370 . 13) (100 . "AcDbPolyline") (90 . 2) (70 . 0)
(43 . 0.0) (10 13099.5475113122 7058.8235294118) (10 13084.4641402715 7058.8235294118))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13084.4641402715 7058.8235294118 0.0) (10 13081.298056773 7081.0859472601 0.0) (10 13085.1180545974
7110.3050326707 0.0) (10 13110.8597285068 7119.1550904977 0.0))
((0 . "LWPOLYLINE") (100 . "AcDbEntity") (8 . "PLANTS") (62 . 94) (370 . 13) (100 . "AcDbPolyline") (90 . 2) (70 . 0)
(43 . 0.0) (10 13099.5475113122 6998.4919683258) (10 13084.4641402715 6998.4919683258))
((0 . "LWPOLYLINE") (100 . "AcDbEntity") (8 . "PLANTS") (62 . 94) (370 . 13) (100 . "AcDbPolyline") (90 . 3) (70 . 0)
(43 . 0.0) (10 13099.5475113122 7047.5113122172) (10 13089.2847285068 7028.6573529412) (10 13084.4641402715
6998.4919683258))
((0 . "LWPOLYLINE") (100 . "AcDbEntity") (8 . "PLANTS") (62 . 94) (370 . 13) (100 . "AcDbPolyline") (90 . 3) (70 . 0)
(43 . 0.0) (10 13084.4641402715 252.6385746606) (10 13099.5502262443 253.8406108597) (10 13112.7446832579
262.0673076923))
((0 . "LWPOLYLINE") (100 . "AcDbEntity") (8 . "PLANTS") (62 . 94) (370 . 13) (100 . "AcDbPolyline") (90 . 2) (70 . 0)
(43 . 0.0) (10 13095.7763574661 6734.5397058824) (10 13088.2352941176 6726.9987556561))
((0 . "LWPOLYLINE") (100 . "AcDbEntity") (8 . "PLANTS") (62 . 94) (370 . 13) (100 . "AcDbPolyline") (90 . 2) (70 . 0)
(43 . 0.0) (10 13122.1719457014 6736.4253393665) (10 13095.7763574661 6734.5397058824))
((0 . "LWPOLYLINE") (100 . "AcDbEntity") (8 . "PLANTS") (62 . 94) (370 . 13) (100 . "AcDbPolyline") (90 . 2) (70 . 0)
(43 . 0.0) (10 13099.5475113122 7058.8235294118) (10 13099.5475113122 7047.5113122172))
((0 . "LWPOLYLINE") (100 . "AcDbEntity") (8 . "PLANTS") (62 . 94) (370 . 13) (100 . "AcDbPolyline") (90 . 3) (70 . 0)
(43 . 0.0) (10 13099.5475113122 7058.8235294118) (10 13122.1788461538 7073.5970588235) (10 13133.4841628959
7066.3652714932))
((0 . "LWPOLYLINE") (100 . "AcDbEntity") (8 . "PLANTS") (62 . 94) (370 . 13) (100 . "AcDbPolyline") (90 . 2) (70 . 0)
(43 . 0.0) (10 13114.6308823529 7036.1990950226) (10 13099.5475113122 7047.5113122172))
((0 . "LWPOLYLINE") (100 . "AcDbEntity") (8 . "PLANTS") (62 . 94) (370 . 13) (100 . "AcDbPolyline") (90 . 3) (70 . 0)
(43 . 0.0) (10 13110.8597285068 6972.0962669683) (10 13104.5159502262 6976.0219457014) (10 13099.5475113122
6998.4919683258))
((0 . "LWPOLYLINE") (100 . "AcDbEntity") (8 . "PLANTS") (62 . 94) (370 . 13) (100 . "AcDbPolyline") (90 . 2) (70 . 0)
(43 . 0.0) (10 13099.5475113122 6998.4919683258) (10 13110.8597285068 7006.032918552))
((0 . "LWPOLYLINE") (100 . "AcDbEntity") (8 . "PLANTS") (62 . 94) (370 . 13) (100 . "AcDbPolyline") (90 . 2) (70 . 0)
(43 . 0.0) (10 13122.1719457014 6783.559841629) (10 13099.5475113122 6783.559841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13099.5475113122 6783.559841629 0.0) (10 13091.102652131 6803.8404001257 0.0) (10 13092.2430496744
6828.5751785307 0.0) (10 13103.3186651584 6847.6618778281 0.0))
((0 . "LWPOLYLINE") (100 . "AcDbEntity") (8 . "PLANTS") (62 . 94) (370 . 13) (100 . "AcDbPolyline") (90 . 2) (70 . 0)
(43 . 0.0) (10 13099.5475113122 369.5333710407) (10 13133.4841628959 369.5333710407))
((0 . "LWPOLYLINE") (100 . "AcDbEntity") (8 . "PLANTS") (62 . 94) (370 . 13) (100 . "AcDbPolyline") (90 . 2) (70 . 0)
(43 . 0.0) (10 13099.5475113122 369.5333710407) (10 13103.3186651584 354.4485294118))
((0 . "LWPOLYLINE") (100 . "AcDbEntity") (8 . "PLANTS") (62 . 94) (370 . 13) (100 . "AcDbPolyline") (90 . 2) (70 . 0)
(43 . 0.0) (10 13103.3186651584 6855.2036199095) (10 13103.3186651584 6847.6618778281))
((0 . "LWPOLYLINE") (100 . "AcDbEntity") (8 . "PLANTS") (62 . 94) (370 . 13) (100 . "AcDbPolyline") (90 . 3) (70 . 0)
(43 . 0.0) (10 13118.4007918552 6881.5985294118) (10 13113.4268099548 6866.5158371041) (10 13103.3186651584
6855.2036199095))
((0 . "LWPOLYLINE") (100 . "AcDbEntity") (8 . "PLANTS") (62 . 94) (370 . 13) (100 . "AcDbPolyline") (90 . 2) (70 . 0)
(43 . 0.0) (10 13144.7963800905 6847.6618778281) (10 13103.3186651584 6847.6618778281))
((0 . "LWPOLYLINE") (100 . "AcDbEntity") (8 . "PLANTS") (62 . 94) (370 . 13) (100 . "AcDbPolyline") (90 . 2) (70 . 0)
(43 . 0.0) (10 13125.9430995475 6700.6030542986) (10 13103.3186651584 6689.2908371041))
((0 . "LWPOLYLINE") (100 . "AcDbEntity") (8 . "PLANTS") (62 . 94) (370 . 13) (100 . "AcDbPolyline") (90 . 2) (70 . 0)
(43 . 0.0) (10 13129.7130090498 6994.7207013575) (10 13110.8597285068 7006.032918552))
((0 . "LWPOLYLINE") (100 . "AcDbEntity") (8 . "PLANTS") (62 . 94) (370 . 13) (100 . "AcDbPolyline") (90 . 3) (70 . 0)
(43 . 0.0) (10 13114.6308823529 7036.1990950226) (10 13114.4831447964 7013.5812217195) (10 13110.8597285068
7006.032918552))
((0 . "LWPOLYLINE") (100 . "AcDbEntity") (8 . "PLANTS") (62 . 94) (370 . 13) (100 . "AcDbPolyline") (90 . 2) (70 . 0)
(43 . 0.0) (10 13110.8597285068 6972.0962669683) (10 13110.8597285068 6945.7013574661))
((0 . "LWPOLYLINE") (100 . "AcDbEntity") (8 . "PLANTS") (62 . 94) (370 . 13) (100 . "AcDbPolyline") (90 . 3) (70 . 0)
(43 . 0.0) (10 13129.7130090498 6994.7207013575) (10 13122.0242081448 6979.6445701357) (10 13110.8597285068
6972.0962669683))
((0 . "LWPOLYLINE") (100 . "AcDbEntity") (8 . "PLANTS") (62 . 94) (370 . 13) (100 . "AcDbPolyline") (90 . 2) (70 . 0)
(43 . 0.0) (10 13152.3374434389 6938.1596153846) (10 13110.8597285068 6945.7013574661))
((0 . "LWPOLYLINE") (100 . "AcDbEntity") (8 . "PLANTS") (62 . 94) (370 . 13) (100 . "AcDbPolyline") (90 . 3) (70 . 0)
(43 . 0.0) (10 13112.7446832579 262.0673076923) (10 13129.7130090498 246.3023755656) (10 13167.4208144796
245.0989819005))
((0 . "LWPOLYLINE") (100 . "AcDbEntity") (8 . "PLANTS") (62 . 94) (370 . 13) (100 . "AcDbPolyline") (90 . 3) (70 . 0)
(43 . 0.0) (10 13148.5675339367 312.9722850679) (10 13143.5921945701 294.1176470588) (10 13112.7446832579
262.0673076923))
((0 . "LWPOLYLINE") (100 . "AcDbEntity") (8 . "PLANTS") (62 . 94) (370 . 13) (100 . "AcDbPolyline") (90 . 2) (70 . 0)
(43 . 0.0) (10 13125.9430995475 7043.7408371041) (10 13114.6308823529 7036.1990950226))
((0 . "LWPOLYLINE") (100 . "AcDbEntity") (8 . "PLANTS") (62 . 94) (370 . 13) (100 . "AcDbPolyline") (90 . 2) (70 . 0)
(43 . 0.0) (10 13114.6308823529 6659.1254524887) (10 13122.1719457014 6662.8959276018))
((0 . "LWPOLYLINE") (100 . "AcDbEntity") (8 . "PLANTS") (62 . 94) (370 . 13) (100 . "AcDbPolyline") (90 . 3) (70 . 0)
(43 . 0.0) (10 13118.4007918552 6881.5985294118) (10 13136.1989819005 6873.9027149321) (10 13144.7963800905
6847.6618778281))
((0 . "LWPOLYLINE") (100 . "AcDbEntity") (8 . "PLANTS") (62 . 94) (370 . 13) (100 . "AcDbPolyline") (90 . 3) (70 . 0)
(43 . 0.0) (10 13118.4007918552 3797.1338235294) (10 13133.4841628959 3793.3639140271) (10 13190.0452488688
3797.1338235294))
((0 . "LWPOLYLINE") (100 . "AcDbEntity") (8 . "PLANTS") (62 . 94) (370 . 13) (100 . "AcDbPolyline") (90 . 2) (70 . 0)
(43 . 0.0) (10 13118.4007918552 3797.1338235294) (10 13129.7130090498 3827.3005656109))
((0 . "LWPOLYLINE") (100 . "AcDbEntity") (8 . "PLANTS") (62 . 94) (370 . 13) (100 . "AcDbPolyline") (90 . 2) (70 . 0)
(43 . 0.0) (10 13122.1719457014 6783.559841629) (10 13129.7130090498 6783.559841629))
((0 . "LWPOLYLINE") (100 . "AcDbEntity") (8 . "PLANTS") (62 . 94) (370 . 13) (100 . "AcDbPolyline") (90 . 2) (70 . 0)
(43 . 0.0) (10 13122.1719457014 6783.559841629) (10 13122.1719457014 6736.4253393665))
((0 . "LWPOLYLINE") (100 . "AcDbEntity") (8 . "PLANTS") (62 . 94) (370 . 13) (100 . "AcDbPolyline") (90 . 2) (70 . 0)
(43 . 0.0) (10 13125.9430995475 6700.6030542986) (10 13122.1719457014 6736.4253393665))
((0 . "LWPOLYLINE") (100 . "AcDbEntity") (8 . "PLANTS") (62 . 94) (370 . 13) (100 . "AcDbPolyline") (90 . 2) (70 . 0)
(43 . 0.0) (10 13122.1719457014 6736.4253393665) (10 13144.7963800905 6738.3109728507))
((0 . "LWPOLYLINE") (100 . "AcDbEntity") (8 . "PLANTS") (62 . 94) (370 . 13) (100 . "AcDbPolyline") (90 . 3) (70 . 0)
(43 . 0.0) (10 13125.9430995475 6700.6030542986) (10 13129.4174208145 6693.0555429864) (10 13125.9430995475
6681.7498868778))
((0 . "LWPOLYLINE") (100 . "AcDbEntity") (8 . "PLANTS") (62 . 94) (370 . 13) (100 . "AcDbPolyline") (90 . 2) (70 . 0)
(43 . 0.0) (10 13125.9430995475 6640.2714932127) (10 13137.2553167421 6610.1053167421))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.618361778)
(40 . 0.7176963527) (40 . 1) (40 . 1) (40 . 1) (40 . 1) (10 13129.7130090498 6994.7207013575 0.0) (10 13160.5840933975
7009.1541410524 0.0) (10 13189.3123542913 7089.3895480218 0.0) (10 13272.4454913913 7099.0285828445 0.0) (10
13241.8095038009 7043.7158444574 0.0) (10 13223.9819004525 7043.7408371041 0.0))
((0 . "LWPOLYLINE") (100 . "AcDbEntity") (8 . "PLANTS") (62 . 94) (370 . 13) (100 . "AcDbPolyline") (90 . 2) (70 . 0)
(43 . 0.0) (10 13205.1286199095 6783.559841629) (10 13129.7130090498 6783.559841629))
((0 . "LWPOLYLINE") (100 . "AcDbEntity") (8 . "PLANTS") (62 . 94) (370 . 13) (100 . "AcDbPolyline") (90 . 3) (70 . 0)
(43 . 0.0) (10 13154.2236425339 6838.2352941176) (10 13142.22239819 6821.2669683258) (10 13129.7130090498
6783.559841629))
((0 . "LWPOLYLINE") (100 . "AcDbEntity") (8 . "PLANTS") (62 . 94) (370 . 13) (100 . "AcDbPolyline") (90 . 3) (70 . 0)
(43 . 0.0) (10 13141.0252262443 354.4485294118) (10 13134.6813348416 358.3744343891) (10 13133.4841628959
369.5333710407))
((0 . "LWPOLYLINE") (100 . "AcDbEntity") (8 . "PLANTS") (62 . 94) (370 . 13) (100 . "AcDbPolyline") (90 . 2) (70 . 0)
(43 . 0.0) (10 13137.2553167421 388.3851809955) (10 13133.4841628959 369.5333710407))
((0 . "LWPOLYLINE") (100 . "AcDbEntity") (8 . "PLANTS") (62 . 94) (370 . 13) (100 . "AcDbPolyline") (90 . 2) (70 . 0)
(43 . 0.0) (10 13137.2553167421 388.3851809955) (10 13161.7647058824 390.2714932127))
((0 . "LWPOLYLINE") (100 . "AcDbEntity") (8 . "PLANTS") (62 . 94) (370 . 13) (100 . "AcDbPolyline") (90 . 2) (70 . 0)
(43 . 0.0) (10 13141.0252262443 3834.8416289593) (10 13148.5675339367 3834.8416289593))
((0 . "LWPOLYLINE") (100 . "AcDbEntity") (8 . "PLANTS") (62 . 94) (370 . 13) (100 . "AcDbPolyline") (90 . 3) (70 . 0)
(43 . 0.0) (10 13141.0252262443 354.4485294118) (10 13141.1729638009 331.8240950226) (10 13148.5675339367
312.9722850679))
((0 . "LWPOLYLINE") (100 . "AcDbEntity") (8 . "PLANTS") (62 . 94) (370 . 13) (100 . "AcDbPolyline") (90 . 3) (70 . 0)
(43 . 0.0) (10 13141.0252262443 354.4485294118) (10 13155.0522624434 365.7683257919) (10 13161.7647058824
390.2714932127))
((0 . "LWPOLYLINE") (100 . "AcDbEntity") (8 . "PLANTS") (62 . 94) (370 . 13) (100 . "AcDbPolyline") (90 . 3) (70 . 0)
(43 . 0.0) (10 13148.5675339367 6843.8914027149) (10 13148.5675339367 6847.6618778281) (10 13144.7963800905
6847.6618778281))
((0 . "LWPOLYLINE") (100 . "AcDbEntity") (8 . "PLANTS") (62 . 94) (370 . 13) (100 . "AcDbPolyline") (90 . 2) (70 . 0)
(43 . 0.0) (10 13148.5675339367 6843.8914027149) (10 13144.7963800905 6847.6618778281))
((0 . "LWPOLYLINE") (100 . "AcDbEntity") (8 . "PLANTS") (62 . 94) (370 . 13) (100 . "AcDbPolyline") (90 . 3) (70 . 0)
(43 . 0.0) (10 13148.5675339367 6843.8914027149) (10 13152.3374434389 6843.8914027149) (10 13154.2236425339
6838.2352941176))
((0 . "LWPOLYLINE") (100 . "AcDbEntity") (8 . "PLANTS") (62 . 94) (370 . 13) (100 . "AcDbPolyline") (90 . 3) (70 . 0)
(43 . 0.0) (10 13148.5675339367 6843.8914027149) (10 13148.5675339367 6840.1209276018) (10 13154.2236425339
6838.2352941176))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13148.5675339367 312.9722850679 0.0) (10 13174.2702513059 303.9567920397 0.0) (10 13178.5700647512
340.274771351 0.0) (10 13201.3574660633 335.596719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13152.3374434389 6938.1596153846 0.0) (10 13158.4517627661 6901.7700723664 0.0) (10 13209.9535691555
6884.8911433285 0.0) (10 13199.4725113122 6842.0057692307 0.0))
((0 . "LWPOLYLINE") (100 . "AcDbEntity") (8 . "PLANTS") (62 . 94) (370 . 13) (100 . "AcDbPolyline") (90 . 2) (70 . 0)
(43 . 0.0) (10 13174.9618778281 6941.9308823529) (10 13152.3374434389 6938.1596153846))
((0 . "LWPOLYLINE") (100 . "AcDbEntity") (8 . "PLANTS") (62 . 94) (370 . 13) (100 . "AcDbPolyline") (90 . 2) (70 . 0)
(43 . 0.0) (10 13171.1919683258 3887.631561086) (10 13152.3374434389 3880.0904977376))
((0 . "LWPOLYLINE") (100 . "AcDbEntity") (8 . "PLANTS") (62 . 94) (370 . 13) (100 . "AcDbPolyline") (90 . 2) (70 . 0)
(43 . 0.0) (10 13154.2236425339 6838.2352941176) (10 13199.4725113122 6842.0057692308))
((0 . "LWPOLYLINE") (100 . "AcDbEntity") (8 . "PLANTS") (62 . 94) (370 . 13) (100 . "AcDbPolyline") (90 . 3) (70 . 0)
(43 . 0.0) (10 13159.8797511312 3744.3438914027) (10 13171.1919683258 3754.4519230769) (10 13182.5041855204
3755.6561085973))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13205.1286199095 467.5707013575 0.0) (10 13173.6123902188 458.6149534072 0.0) (10 13163.7016397117
418.3341320015 0.0) (10 13161.7647058824 390.2714932127 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13205.1286199095 365.7607466063 0.0) (10 13205.5932489208 388.0774818479 0.0) (10 13179.479696554
396.8498408013 0.0) (10 13161.7647058824 390.2714932127 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13167.4208144796 245.0989819004 0.0) (10 13186.8002307312 224.6214382184 0.0) (10 13228.9599697698
225.900792548 0.0) (10 13250.3774886878 245.0989819004 0.0))
((0 . "LWPOLYLINE") (100 . "AcDbEntity") (8 . "PLANTS") (62 . 94) (370 . 13) (100 . "AcDbPolyline") (90 . 3) (70 . 0)
(43 . 0.0) (10 13167.4208144796 245.0989819005) (10 13181.4478506787 271.4932126697) (10 13182.5041855204
282.8054298643))
((0 . "LWPOLYLINE") (100 . "AcDbEntity") (8 . "PLANTS") (62 . 94) (370 . 13) (100 . "AcDbPolyline") (90 . 3) (70 . 0)
(43 . 0.0) (10 13171.1919683258 3887.631561086) (10 13186.2740950226 3877.3760180995) (10 13201.3574660633
3876.3193438914))
((0 . "LWPOLYLINE") (100 . "AcDbEntity") (8 . "PLANTS") (62 . 94) (370 . 13) (100 . "AcDbPolyline") (90 . 2) (70 . 0)
(43 . 0.0) (10 13171.1919683258 3887.631561086) (10 13186.2740950226 3906.4860859729))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13174.961877828 6941.930882353 0.0) (10 13201.7442766811 6907.2005094309 0.0) (10 13230.4485539357
6958.2326956203 0.0) (10 13257.9185520362 6934.3891402715 0.0))
((0 . "LWPOLYLINE") (100 . "AcDbEntity") (8 . "PLANTS") (62 . 94) (370 . 13) (100 . "AcDbPolyline") (90 . 3) (70 . 0)
(43 . 0.0) (10 13174.9618778281 6941.9308823529) (10 13178.8876696833 6953.2430995475) (10 13205.1286199095
6979.6380090498))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13178.7330316742 6738.3109728507 0.0) (10 13236.879020511 6759.0195664736 0.0) (10 13290.903361796
6718.3829953421 0.0) (10 13348.4162895928 6738.3109728507 0.0))
((0 . "LWPOLYLINE") (100 . "AcDbEntity") (8 . "PLANTS") (62 . 94) (370 . 13) (100 . "AcDbPolyline") (90 . 3) (70 . 0)
(43 . 0.0) (10 13182.5041855204 3827.3005656109) (10 13201.3574660633 3834.6869909502) (10 13220.2107466063
3823.5294117647))
((0 . "LWPOLYLINE") (100 . "AcDbEntity") (8 . "PLANTS") (62 . 94) (370 . 13) (100 . "AcDbPolyline") (90 . 2) (70 . 0)
(43 . 0.0) (10 13182.5041855204 3755.6561085973) (10 13198.6638863333 3733.0316742081))
((0 . "LWPOLYLINE") (100 . "AcDbEntity") (8 . "PLANTS") (62 . 94) (370 . 13) (100 . "AcDbPolyline") (90 . 2) (70 . 0)
(43 . 0.0) (10 13182.5041855204 3755.6561085973) (10 13190.0452488688 3797.1338235294))
((0 . "LWPOLYLINE") (100 . "AcDbEntity") (8 . "PLANTS") (62 . 94) (370 . 13) (100 . "AcDbPolyline") (90 . 2) (70 . 0)
(43 . 0.0) (10 13220.2107466063 3804.6761312217) (10 13190.0452488688 3797.1338235294))
((0 . "LWPOLYLINE") (100 . "AcDbEntity") (8 . "PLANTS") (62 . 94) (370 . 13) (100 . "AcDbPolyline") (90 . 2) (70 . 0)
(43 . 0.0) (10 13199.4725113122 6842.0057692308) (10 13205.1286199095 6783.559841629))
((0 . "LWPOLYLINE") (100 . "AcDbEntity") (8 . "PLANTS") (62 . 94) (370 . 13) (100 . "AcDbPolyline") (90 . 2) (70 . 0)
(43 . 0.0) (10 13212.6696832579 6843.8914027149) (10 13199.4725113122 6842.0057692308))
((0 . "LWPOLYLINE") (100 . "AcDbEntity") (8 . "PLANTS") (62 . 94) (370 . 13) (100 . "AcDbPolyline") (90 . 3) (70 . 0)
(43 . 0.0) (10 13201.3574660633 335.596719457) (10 13239.0652714932 321.5627828054) (10 13257.9185520362
320.5118778281))
((0 . "LWPOLYLINE") (100 . "AcDbEntity") (8 . "PLANTS") (62 . 94) (370 . 13) (100 . "AcDbPolyline") (90 . 2) (70 . 0)
(43 . 0.0) (10 13201.3574660633 335.596719457) (10 13205.1286199095 365.7607466063))
((0 . "LWPOLYLINE") (100 . "AcDbEntity") (8 . "PLANTS") (62 . 94) (370 . 13) (100 . "AcDbPolyline") (90 . 2) (70 . 0)
(43 . 0.0) (10 13205.1286199095 6979.6380090498) (10 13205.1286199095 6994.7207013575))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13205.1286199095 6979.6380090498 0.0) (10 13264.4241536653 6987.2573213791 0.0) (10 13298.3511802555
7047.4119414315 0.0) (10 13359.7285067873 7051.2817873303 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.1846116746)
(40 . 0.6159574034) (40 . 1) (40 . 1) (40 . 1) (40 . 1) (10 13205.1286199095 6783.5598416289 0.0) (10 13218.9183620921
6780.7556402068 0.0) (10 13265.3516643057 6784.2799618777 0.0) (10 13341.1338458366 6778.7511257556 0.0) (10
13402.637271829 6787.4532128155 0.0) (10 13431.3729638009 6779.7885746607 0.0))
((0 . "LWPOLYLINE") (100 . "AcDbEntity") (8 . "PLANTS") (62 . 94) (370 . 13) (100 . "AcDbPolyline") (90 . 3) (70 . 0)
(43 . 0.0) (10 13205.1286199095 467.5707013575) (10 13208.8985294118 448.7188914027) (10 13205.1286199095
422.3218325792))
((0 . "LWPOLYLINE") (100 . "AcDbEntity") (8 . "PLANTS") (62 . 94) (370 . 13) (100 . "AcDbPolyline") (90 . 3) (70 . 0)
(43 . 0.0) (10 13205.1286199095 467.5707013575) (10 13209.9479638009 493.967760181) (10 13225.4505749053
530.0804711057))
((0 . "LWPOLYLINE") (100 . "AcDbEntity") (8 . "PLANTS") (62 . 94) (370 . 13) (100 . "AcDbPolyline") (90 . 2) (70 . 0)
(43 . 0.0) (10 13242.8351809955 373.3031674208) (10 13205.1286199095 365.7607466063))
((0 . "LWPOLYLINE") (100 . "AcDbEntity") (8 . "PLANTS") (62 . 94) (370 . 13) (100 . "AcDbPolyline") (90 . 2) (70 . 0)
(43 . 0.0) (10 13212.6696832579 7028.6573529412) (10 13223.9819004525 7043.7408371041))
((0 . "LWPOLYLINE") (100 . "AcDbEntity") (8 . "PLANTS") (62 . 94) (370 . 13) (100 . "AcDbPolyline") (90 . 3) (70 . 0)
(43 . 0.0) (10 13212.6696832579 6843.8914027149) (10 13223.9819004525 6830.0130090498) (10 13239.0652714932
6825.0374434389))
((0 . "LWPOLYLINE") (100 . "AcDbEntity") (8 . "PLANTS") (62 . 94) (370 . 13) (100 . "AcDbPolyline") (90 . 3) (70 . 0)
(43 . 0.0) (10 13212.6696832579 6843.8914027149) (10 13223.9819004525 6851.278280543) (10 13276.7718325792
6855.2036199095))
((0 . "LWPOLYLINE") (100 . "AcDbEntity") (8 . "PLANTS") (62 . 94) (370 . 13) (100 . "AcDbPolyline") (90 . 2) (70 . 0)
(43 . 0.0) (10 13216.4408371041 7055.0530542986) (10 13223.9819004525 7043.7408371041))
((0 . "LWPOLYLINE") (100 . "AcDbEntity") (8 . "PLANTS") (62 . 94) (370 . 13) (100 . "AcDbPolyline") (90 . 2) (70 . 0)
(43 . 0.0) (10 13220.2107466063 3804.6761312217) (10 13220.2107466063 3823.5294117647))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13291.8552036199 3834.8416289593 0.0) (10 13270.4974146508 3851.2671141775 0.0) (10 13236.7428155427
3844.0489696983 0.0) (10 13220.2107466063 3823.5294117647 0.0))
((0 . "LWPOLYLINE") (100 . "AcDbEntity") (8 . "PLANTS") (62 . 94) (370 . 13) (100 . "AcDbPolyline") (90 . 2) (70 . 0)
(43 . 0.0) (10 13220.2107466063 3804.6761312217) (10 13242.8351809955 3797.1338235294))
((0 . "LWPOLYLINE") (100 . "AcDbEntity") (8 . "PLANTS") (62 . 94) (370 . 13) (100 . "AcDbPolyline") (90 . 3) (70 . 0)
(43 . 0.0) (10 13288.0840497738 3910.2559954751) (10 13250.3774886878 3910.4109728507) (10 13223.9819004525
3925.3393665158))
((0 . "LWPOLYLINE") (100 . "AcDbEntity") (8 . "PLANTS") (62 . 94) (370 . 13) (100 . "AcDbPolyline") (90 . 3) (70 . 0)
(43 . 0.0) (10 13257.9185520362 3876.3193438914) (10 13235.3010180995 3876.1714932127) (10 13227.7530542986
3872.5494343891))
((0 . "LWPOLYLINE") (100 . "AcDbEntity") (8 . "PLANTS") (62 . 94) (370 . 13) (100 . "AcDbPolyline") (90 . 2) (70 . 0)
(43 . 0.0) (10 13235.2941176471 6911.7647058824) (10 13276.7718325792 6866.5158371041))
((0 . "LWPOLYLINE") (100 . "AcDbEntity") (8 . "PLANTS") (62 . 94) (370 . 13) (100 . "AcDbPolyline") (90 . 2) (70 . 0)
(43 . 0.0) (10 13242.8351809955 3797.1338235294) (10 13236.0878793211 3733.0316742081))
((0 . "LWPOLYLINE") (100 . "AcDbEntity") (8 . "PLANTS") (62 . 94) (370 . 13) (100 . "AcDbPolyline") (90 . 3) (70 . 0)
(43 . 0.0) (10 13291.8552036199 3808.446040724) (10 13269.2307692308 3797.282239819) (10 13242.8351809955
3797.1338235294))
((0 . "LWPOLYLINE") (100 . "AcDbEntity") (8 . "PLANTS") (62 . 94) (370 . 13) (100 . "AcDbPolyline") (90 . 2) (70 . 0)
(43 . 0.0) (10 13242.8351809955 388.3851809955) (10 13242.8351809955 373.3031674208))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7570375263) (40
. 1) (40 . 1) (40 . 1) (40 . 1) (10 13242.8351809954 388.3851809955 0.0) (10 13209.232069364 409.6997866274 0.0) (10
13264.6050056868 470.4549372743 0.0) (10 13306.5888944584 457.9871255666 0.0) (10 13314.479638009 448.7188914027 0.0))
((0 . "LWPOLYLINE") (100 . "AcDbEntity") (8 . "PLANTS") (62 . 94) (370 . 13) (100 . "AcDbPolyline") (90 . 2) (70 . 0)
(43 . 0.0) (10 13242.8351809955 388.3851809955) (10 13276.7718325792 399.69739819))
((0 . "LWPOLYLINE") (100 . "AcDbEntity") (8 . "PLANTS") (62 . 94) (370 . 13) (100 . "AcDbPolyline") (90 . 2) (70 . 0)
(43 . 0.0) (10 13242.8351809955 373.3031674208) (10 13261.6897058824 354.4485294118))
((0 . "LWPOLYLINE") (100 . "AcDbEntity") (8 . "PLANTS") (62 . 94) (370 . 13) (100 . "AcDbPolyline") (90 . 2) (70 . 0)
(43 . 0.0) (10 13246.6063348416 3955.5048642534) (10 13261.6897058824 3959.2760180995))
((0 . "LWPOLYLINE") (100 . "AcDbEntity") (8 . "PLANTS") (62 . 94) (370 . 13) (100 . "AcDbPolyline") (90 . 2) (70 . 0)
(43 . 0.0) (10 13295.6263574661 995.4751131222) (10 13279.447150118 994.2308803775))
((0 . "LWPOLYLINE") (100 . "AcDbEntity") (8 . "PLANTS") (62 . 94) (370 . 13) (100 . "AcDbPolyline") (90 . 3) (70 . 0)
(43 . 0.0) (10 13250.3774886878 245.0989819005) (10 13261.6897058824 237.711199095) (10 13306.9385746606 237.556561086))
((0 . "LWPOLYLINE") (100 . "AcDbEntity") (8 . "PLANTS") (62 . 94) (370 . 13) (100 . "AcDbPolyline") (90 . 2) (70 . 0)
(43 . 0.0) (10 13257.9185520362 320.5118778281) (10 13250.3774886878 245.0989819005))
((0 . "LWPOLYLINE") (100 . "AcDbEntity") (8 . "PLANTS") (62 . 94) (370 . 13) (100 . "AcDbPolyline") (90 . 2) (70 . 0)
(43 . 0.0) (10 13257.9185520362 320.5118778281) (10 13261.6897058824 354.4485294118))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13329.5630090498 4023.3781674208 0.0) (10 13307.6169192682 4032.9087334629 0.0) (10 13252.583865192
4040.297735602 0.0) (10 13261.6897058823 4072.3981900452 0.0))
((0 . "LWPOLYLINE") (100 . "AcDbEntity") (8 . "PLANTS") (62 . 94) (370 . 13) (100 . "AcDbPolyline") (90 . 2) (70 . 0)
(43 . 0.0) (10 13284.3141402715 3947.963800905) (10 13261.6897058824 3959.2760180995))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3356698935)
(40 . 0.4024927711) (40 . 1) (40 . 1) (40 . 1) (40 . 1) (10 13261.6897058824 3959.2760180996 0.0) (10 13266.557946247
3980.7746088735 0.0) (10 13208.517583592 3990.1163420059 0.0) (10 13251.959825965 4033.9705722095 0.0) (10
13297.5510389187 3981.2218143198 0.0) (10 13329.5630090497 3993.2126696832 0.0))
((0 . "LWPOLYLINE") (100 . "AcDbEntity") (8 . "PLANTS") (62 . 94) (370 . 13) (100 . "AcDbPolyline") (90 . 3) (70 . 0)
(43 . 0.0) (10 13284.3141402715 373.3031674208) (10 13276.6239819005 358.3744343891) (10 13261.6897058824
354.4485294118))
((0 . "LWPOLYLINE") (100 . "AcDbEntity") (8 . "PLANTS") (62 . 94) (370 . 13) (100 . "AcDbPolyline") (90 . 3) (70 . 0)
(43 . 0.0) (10 13265.4596153846 6975.8675339367) (10 13288.0840497738 6980.8291855204) (10 13303.1674208145
6990.9502262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13363.4996606335 965.3082579185 0.0) (10 13337.0560485003 981.7974924008 0.0) (10 13299.6021015498
971.9307911047 0.0) (10 13280.895343149 947.9297919672 0.0))
((0 . "LWPOLYLINE") (100 . "AcDbEntity") (8 . "PLANTS") (62 . 94) (370 . 13) (100 . "AcDbPolyline") (90 . 2) (70 . 0)
(43 . 0.0) (10 13276.7718325792 6855.2036199095) (10 13276.7718325792 6866.5158371041))
((0 . "LWPOLYLINE") (100 . "AcDbEntity") (8 . "PLANTS") (62 . 94) (370 . 13) (100 . "AcDbPolyline") (90 . 2) (70 . 0)
(43 . 0.0) (10 13295.6263574661 6881.5985294118) (10 13276.7718325792 6866.5158371041))
((0 . "LWPOLYLINE") (100 . "AcDbEntity") (8 . "PLANTS") (62 . 94) (370 . 13) (100 . "AcDbPolyline") (90 . 3) (70 . 0)
(43 . 0.0) (10 13276.7718325792 6855.2036199095) (10 13291.8552036199 6841.3252262443) (10 13322.0207013575
6840.1209276018))
((0 . "LWPOLYLINE") (100 . "AcDbEntity") (8 . "PLANTS") (62 . 94) (370 . 13) (100 . "AcDbPolyline") (90 . 3) (70 . 0)
(43 . 0.0) (10 13276.7718325792 4083.7104072398) (10 13314.4796380091 4069.6774886878) (10 13329.5630090498
4068.6270361991))
((0 . "LWPOLYLINE") (100 . "AcDbEntity") (8 . "PLANTS") (62 . 94) (370 . 13) (100 . "AcDbPolyline") (90 . 2) (70 . 0)
(43 . 0.0) (10 13276.7718325792 399.69739819) (10 13276.7718325792 422.3218325792))
((0 . "LWPOLYLINE") (100 . "AcDbEntity") (8 . "PLANTS") (62 . 94) (370 . 13) (100 . "AcDbPolyline") (90 . 2) (70 . 0)
(43 . 0.0) (10 13284.3141402715 373.3031674208) (10 13276.7718325792 399.69739819))
((0 . "LWPOLYLINE") (100 . "AcDbEntity") (8 . "PLANTS") (62 . 94) (370 . 13) (100 . "AcDbPolyline") (90 . 2) (70 . 0)
(43 . 0.0) (10 13291.8552036199 6900.4524886878) (10 13284.3141402715 6900.4524886878))
((0 . "LWPOLYLINE") (100 . "AcDbEntity") (8 . "PLANTS") (62 . 94) (370 . 13) (100 . "AcDbPolyline") (90 . 3) (70 . 0)
(43 . 0.0) (10 13284.3141402715 3947.963800905) (10 13284.4619909502 3925.3455882353) (10 13288.0840497738
3917.7983031674))
((0 . "LWPOLYLINE") (100 . "AcDbEntity") (8 . "PLANTS") (62 . 94) (370 . 13) (100 . "AcDbPolyline") (90 . 3) (70 . 0)
(43 . 0.0) (10 13333.332918552 3963.0471719457) (10 13318.2507918552 3952.938800905) (10 13284.3141402715
3947.963800905))
((0 . "LWPOLYLINE") (100 . "AcDbEntity") (8 . "PLANTS") (62 . 94) (370 . 13) (100 . "AcDbPolyline") (90 . 2) (70 . 0)
(43 . 0.0) (10 13286.1990950226 3733.0316742081) (10 13284.3141402715 3736.8028280543))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13313.3849646895 1102.8318870063 0.0) (10 13339.1835018387 1095.0344012727 0.0) (10 13366.645809043
1117.0184560636 0.0) (10 13389.8940045249 1093.5152714932 0.0))
((0 . "LWPOLYLINE") (100 . "AcDbEntity") (8 . "PLANTS") (62 . 94) (370 . 13) (100 . "AcDbPolyline") (90 . 3) (70 . 0)
(43 . 0.0) (10 13284.3141402715 373.3031674208) (10 13306.9385746606 378.1300904977) (10 13329.5630090498
392.1578054299))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13288.0840497738 3917.7983031674 0.0) (10 13295.3342759869 3909.6192719706 0.0) (10 13352.4967440342
3926.4327077737 0.0) (10 13359.7285067873 3898.9437782805 0.0))
((0 . "LWPOLYLINE") (100 . "AcDbEntity") (8 . "PLANTS") (62 . 94) (370 . 13) (100 . "AcDbPolyline") (90 . 2) (70 . 0)
(43 . 0.0) (10 13288.0840497738 3910.2559954751) (10 13288.0840497738 3917.7983031674))
((0 . "LWPOLYLINE") (100 . "AcDbEntity") (8 . "PLANTS") (62 . 94) (370 . 13) (100 . "AcDbPolyline") (90 . 3) (70 . 0)
(43 . 0.0) (10 13288.0840497738 3910.2559954751) (10 13299.2484162896 3865.0071266968) (10 13295.6263574661
3842.3826923077))
((0 . "LWPOLYLINE") (100 . "AcDbEntity") (8 . "PLANTS") (62 . 94) (370 . 13) (100 . "AcDbPolyline") (90 . 2) (70 . 0)
(43 . 0.0) (10 13291.8552036199 6900.4524886878) (10 13295.6263574661 6881.5985294118))
((0 . "LWPOLYLINE") (100 . "AcDbEntity") (8 . "PLANTS") (62 . 94) (370 . 13) (100 . "AcDbPolyline") (90 . 2) (70 . 0)
(43 . 0.0) (10 13291.8552036199 6900.4524886878) (10 13295.6263574661 6915.5351809955))
((0 . "LWPOLYLINE") (100 . "AcDbEntity") (8 . "PLANTS") (62 . 94) (370 . 13) (100 . "AcDbPolyline") (90 . 2) (70 . 0)
(43 . 0.0) (10 13291.8552036199 3834.8416289593) (10 13291.8552036199 3808.446040724))
((0 . "LWPOLYLINE") (100 . "AcDbEntity") (8 . "PLANTS") (62 . 94) (370 . 13) (100 . "AcDbPolyline") (90 . 2) (70 . 0)
(43 . 0.0) (10 13291.8552036199 3834.8416289593) (10 13295.6263574661 3842.3826923077))
((0 . "LWPOLYLINE") (100 . "AcDbEntity") (8 . "PLANTS") (62 . 94) (370 . 13) (100 . "AcDbPolyline") (90 . 3) (70 . 0)
(43 . 0.0) (10 13291.8552036199 3808.446040724) (10 13303.1674208145 3798.3385746606) (10 13337.1040723982
3789.592760181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13295.6263574661 6881.5985294118 0.0) (10 13315.5068179819 6881.6213042519 0.0) (10 13328.4077225334
6858.8001823212 0.0) (10 13322.0207013575 6840.1209276018 0.0))
((0 . "LWPOLYLINE") (100 . "AcDbEntity") (8 . "PLANTS") (62 . 94) (370 . 13) (100 . "AcDbPolyline") (90 . 2) (70 . 0)
(43 . 0.0) (10 13352.1874434389 3842.3826923077) (10 13295.6263574661 3842.3826923077))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13309.8470716565 914.1527753751 0.0) (10 13311.7788001555 918.9242690855 0.0) (10 13305.9915714168
929.4281666217 0.0) (10 13300.2740130384 925.3213437629 0.0))
((0 . "LWPOLYLINE") (100 . "AcDbEntity") (8 . "PLANTS") (62 . 94) (370 . 13) (100 . "AcDbPolyline") (90 . 2) (70 . 0)
(43 . 0.0) (10 13306.9385746606 260.1809954751) (10 13306.9385746606 237.556561086))
((0 . "LWPOLYLINE") (100 . "AcDbEntity") (8 . "PLANTS") (62 . 94) (370 . 13) (100 . "AcDbPolyline") (90 . 3) (70 . 0)
(43 . 0.0) (10 13378.5817873303 241.3263574661) (10 13363.4996606335 237.7042986425) (10 13306.9385746606
237.556561086))
((0 . "LWPOLYLINE") (100 . "AcDbEntity") (8 . "PLANTS") (62 . 94) (370 . 13) (100 . "AcDbPolyline") (90 . 3) (70 . 0)
(43 . 0.0) (10 13378.5817873303 904.9773755656) (10 13367.2695701357 901.354638009) (10 13322.2055201949
899.7345854137))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13314.4796380091 448.7188914027 0.0) (10 13286.4063933218 421.4561382771 0.0) (10 13335.5034983616
416.8974001575 0.0) (10 13329.5630090498 392.1578054299 0.0))
((0 . "LWPOLYLINE") (100 . "AcDbEntity") (8 . "PLANTS") (62 . 94) (370 . 13) (100 . "AcDbPolyline") (90 . 2) (70 . 0)
(43 . 0.0) (10 13314.4796380091 448.7188914027) (10 13333.332918552 460.0311085973))
((0 . "LWPOLYLINE") (100 . "AcDbEntity") (8 . "PLANTS") (62 . 94) (370 . 13) (100 . "AcDbPolyline") (90 . 2) (70 . 0)
(43 . 0.0) (10 13371.0407239819 6840.1209276018) (10 13322.0207013575 6840.1209276018))
((0 . "LWPOLYLINE") (100 . "AcDbEntity") (8 . "PLANTS") (62 . 94) (370 . 13) (100 . "AcDbPolyline") (90 . 2) (70 . 0)
(43 . 0.0) (10 13322.0207013575 1059.5786199095) (10 13329.5630090498 1059.5786199095))
((0 . "LWPOLYLINE") (100 . "AcDbEntity") (8 . "PLANTS") (62 . 94) (370 . 13) (100 . "AcDbPolyline") (90 . 3) (70 . 0)
(43 . 0.0) (10 13340.8752262443 6949.4718325792) (10 13329.5630090498 6949.4718325792) (10 13325.7918552036
6945.7013574661))
((0 . "LWPOLYLINE") (100 . "AcDbEntity") (8 . "PLANTS") (62 . 94) (370 . 13) (100 . "AcDbPolyline") (90 . 2) (70 . 0)
(43 . 0.0) (10 13325.7918552036 4151.5837104072) (10 13329.5630090498 4068.6270361991))
((0 . "LWPOLYLINE") (100 . "AcDbEntity") (8 . "PLANTS") (62 . 94) (370 . 13) (100 . "AcDbPolyline") (90 . 3) (70 . 0)
(43 . 0.0) (10 13325.7918552036 4151.5837104072) (10 13306.9385746606 4156.5455882353) (10 13296.2186223015
4164.5106095638))
((0 . "LWPOLYLINE") (100 . "AcDbEntity") (8 . "PLANTS") (62 . 94) (370 . 13) (100 . "AcDbPolyline") (90 . 3) (70 . 0)
(43 . 0.0) (10 13291.9486084277 4207.2107483021) (10 13314.4796380091 4197.8892533937) (10 13329.5630090498
4196.8325791855))
((0 . "LWPOLYLINE") (100 . "AcDbEntity") (8 . "PLANTS") (62 . 94) (370 . 13) (100 . "AcDbPolyline") (90 . 2) (70 . 0)
(43 . 0.0) (10 13325.7918552036 4151.5837104072) (10 13333.332918552 4170.4369909502))
((0 . "LWPOLYLINE") (100 . "AcDbEntity") (8 . "PLANTS") (62 . 94) (370 . 13) (100 . "AcDbPolyline") (90 . 2) (70 . 0)
(43 . 0.0) (10 13325.7918552036 3755.6561085973) (10 13337.1040723982 3789.592760181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13325.7918552036 550.5288461538 0.0) (10 13359.9364726119 533.1659007453 0.0) (10 13328.7848038512
476.0914654482 0.0) (10 13367.2695701357 467.5707013575 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13371.0407239819 6840.1209276018 0.0) (10 13386.8074144616 6872.6858439205 0.0) (10 13358.469435466
6901.6425555369 0.0) (10 13329.5630090498 6911.7647058823 0.0))
((0 . "LWPOLYLINE") (100 . "AcDbEntity") (8 . "PLANTS") (62 . 94) (370 . 13) (100 . "AcDbPolyline") (90 . 2) (70 . 0)
(43 . 0.0) (10 13329.5630090498 4291.8549547511) (10 13329.5630090498 4196.8325791855))
((0 . "LWPOLYLINE") (100 . "AcDbEntity") (8 . "PLANTS") (62 . 94) (370 . 13) (100 . "AcDbPolyline") (90 . 2) (70 . 0)
(43 . 0.0) (10 13333.332918552 4170.4369909502) (10 13329.5630090498 4196.8325791855))
((0 . "LWPOLYLINE") (100 . "AcDbEntity") (8 . "PLANTS") (62 . 94) (370 . 13) (100 . "AcDbPolyline") (90 . 2) (70 . 0)
(43 . 0.0) (10 13333.332918552 4061.0859728507) (10 13329.5630090498 4068.6270361991))
((0 . "LWPOLYLINE") (100 . "AcDbEntity") (8 . "PLANTS") (62 . 94) (370 . 13) (100 . "AcDbPolyline") (90 . 2) (70 . 0)
(43 . 0.0) (10 13329.5630090498 4023.3781674208) (10 13329.5630090498 3993.2126696833))
((0 . "LWPOLYLINE") (100 . "AcDbEntity") (8 . "PLANTS") (62 . 94) (370 . 13) (100 . "AcDbPolyline") (90 . 3) (70 . 0)
(43 . 0.0) (10 13329.5630090498 4023.3781674208) (10 13329.7108597285 4053.5380090498) (10 13333.332918552
4061.0859728507))
((0 . "LWPOLYLINE") (100 . "AcDbEntity") (8 . "PLANTS") (62 . 94) (370 . 13) (100 . "AcDbPolyline") (90 . 2) (70 . 0)
(43 . 0.0) (10 13333.332918552 3963.0471719457) (10 13329.5630090498 3993.2126696833))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13401.2062217195 995.4751131222 0.0) (10 13386.5939853647 1030.6248156069 0.0) (10 13327.2526918434
1012.958715926 0.0) (10 13329.5630090498 1059.5786199096 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4602420022) (40
. 1) (40 . 1) (40 . 1) (40 . 1) (10 13329.5630090496 1059.5786199095 0.0) (10 13345.2019902564 1079.6221817911 0.0) (10
13403.4271513415 1080.2284805796 0.0) (10 13431.6323181257 1026.6401130788 0.0) (10 13416.2895927601 999.2449095022
0.0))
((0 . "LWPOLYLINE") (100 . "AcDbEntity") (8 . "PLANTS") (62 . 94) (370 . 13) (100 . "AcDbPolyline") (90 . 3) (70 . 0)
(43 . 0.0) (10 13329.5630090498 392.1578054299) (10 13363.492760181 392.3048642534) (10 13371.0407239819 395.92760181))
((0 . "LWPOLYLINE") (100 . "AcDbEntity") (8 . "PLANTS") (62 . 94) (370 . 13) (100 . "AcDbPolyline") (90 . 2) (70 . 0)
(43 . 0.0) (10 13352.1874434389 301.6600678733) (10 13329.5630090498 275.2630090498))
((0 . "LWPOLYLINE") (100 . "AcDbEntity") (8 . "PLANTS") (62 . 94) (370 . 13) (100 . "AcDbPolyline") (90 . 3) (70 . 0)
(43 . 0.0) (10 13401.2062217195 4147.8125565611) (10 13378.5817873303 4148.8630090498) (10 13333.332918552
4170.4369909502))
((0 . "LWPOLYLINE") (100 . "AcDbEntity") (8 . "PLANTS") (62 . 94) (370 . 13) (100 . "AcDbPolyline") (90 . 2) (70 . 0)
(43 . 0.0) (10 13333.332918552 4061.0859728507) (10 13374.8118778281 4053.5449095023))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13333.332918552 3963.0471719457 0.0) (10 13351.1893350568 3953.0516745057 0.0) (10 13381.6144296734
3938.0185623142 0.0) (10 13401.2062217195 3955.5048642534 0.0))
((0 . "LWPOLYLINE") (100 . "AcDbEntity") (8 . "PLANTS") (62 . 94) (370 . 13) (100 . "AcDbPolyline") (90 . 2) (70 . 0)
(43 . 0.0) (10 13371.0407239819 3800.9049773756) (10 13337.1040723982 3789.592760181))
((0 . "LWPOLYLINE") (100 . "AcDbEntity") (8 . "PLANTS") (62 . 94) (370 . 13) (100 . "AcDbPolyline") (90 . 2) (70 . 0)
(43 . 0.0) (10 13340.8752262443 935.1442307692) (10 13359.7285067873 938.9140271493))
((0 . "LWPOLYLINE") (100 . "AcDbEntity") (8 . "PLANTS") (62 . 94) (370 . 13) (100 . "AcDbPolyline") (90 . 2) (70 . 0)
(43 . 0.0) (10 13344.6451357466 324.2845022624) (10 13363.4996606335 331.8240950226))
((0 . "LWPOLYLINE") (100 . "AcDbEntity") (8 . "PLANTS") (62 . 94) (370 . 13) (100 . "AcDbPolyline") (90 . 2) (70 . 0)
(43 . 0.0) (10 13352.1874434389 3842.3826923077) (10 13371.0407239819 3800.9049773756))
((0 . "LWPOLYLINE") (100 . "AcDbEntity") (8 . "PLANTS") (62 . 94) (370 . 13) (100 . "AcDbPolyline") (90 . 2) (70 . 0)
(43 . 0.0) (10 13352.1874434389 3842.3826923077) (10 13363.4996606335 3857.4660633484))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13438.9140271493 3865.0071266968 0.0) (10 13429.0137929536 3895.584617153 0.0) (10 13387.6607243805
3906.1189102767 0.0) (10 13359.7285067873 3898.9437782805 0.0))
((0 . "LWPOLYLINE") (100 . "AcDbEntity") (8 . "PLANTS") (62 . 94) (370 . 13) (100 . "AcDbPolyline") (90 . 3) (70 . 0)
(43 . 0.0) (10 13363.4996606335 3857.4660633484) (10 13359.8762443439 3865.0140271493) (10 13359.7285067873
3898.9437782805))
((0 . "LWPOLYLINE") (100 . "AcDbEntity") (8 . "PLANTS") (62 . 94) (370 . 13) (100 . "AcDbPolyline") (90 . 2) (70 . 0)
(43 . 0.0) (10 13359.7285067873 938.9140271493) (10 13378.5817873303 935.1442307692))
((0 . "LWPOLYLINE") (100 . "AcDbEntity") (8 . "PLANTS") (62 . 94) (370 . 13) (100 . "AcDbPolyline") (90 . 2) (70 . 0)
(43 . 0.0) (10 13359.7285067873 938.9140271493) (10 13363.4996606335 965.3082579186))
((0 . "LWPOLYLINE") (100 . "AcDbEntity") (8 . "PLANTS") (62 . 94) (370 . 13) (100 . "AcDbPolyline") (90 . 2) (70 . 0)
(43 . 0.0) (10 13374.8118778281 3857.4660633484) (10 13363.4996606335 3857.4660633484))
((0 . "LWPOLYLINE") (100 . "AcDbEntity") (8 . "PLANTS") (62 . 94) (370 . 13) (100 . "AcDbPolyline") (90 . 2) (70 . 0)
(43 . 0.0) (10 13363.4996606335 965.3082579186) (10 13389.8940045249 969.0808823529))
((0 . "LWPOLYLINE") (100 . "AcDbEntity") (8 . "PLANTS") (62 . 94) (370 . 13) (100 . "AcDbPolyline") (90 . 2) (70 . 0)
(43 . 0.0) (10 13371.0407239819 395.92760181) (10 13367.2695701357 467.5707013575))
((0 . "LWPOLYLINE") (100 . "AcDbEntity") (8 . "PLANTS") (62 . 94) (370 . 13) (100 . "AcDbPolyline") (90 . 2) (70 . 0)
(43 . 0.0) (10 13382.3529411765 475.1131221719) (10 13367.2695701357 467.5707013575))
((0 . "LWPOLYLINE") (100 . "AcDbEntity") (8 . "PLANTS") (62 . 94) (370 . 13) (100 . "AcDbPolyline") (90 . 2) (70 . 0)
(43 . 0.0) (10 13371.0407239819 6840.1209276018) (10 13389.8940045249 6836.3496606335))
((0 . "LWPOLYLINE") (100 . "AcDbEntity") (8 . "PLANTS") (62 . 94) (370 . 13) (100 . "AcDbPolyline") (90 . 2) (70 . 0)
(43 . 0.0) (10 13371.0407239819 3800.9049773756) (10 13408.7485294118 3808.446040724))
((0 . "LWPOLYLINE") (100 . "AcDbEntity") (8 . "PLANTS") (62 . 94) (370 . 13) (100 . "AcDbPolyline") (90 . 2) (70 . 0)
(43 . 0.0) (10 13382.3529411765 395.92760181) (10 13371.0407239819 395.92760181))
((0 . "LWPOLYLINE") (100 . "AcDbEntity") (8 . "PLANTS") (62 . 94) (370 . 13) (100 . "AcDbPolyline") (90 . 3) (70 . 0)
(43 . 0.0) (10 13393.665158371 4061.0859728507) (10 13384.9269230769 4091.2514705882) (10 13374.8118778281
4102.5636877828))
((0 . "LWPOLYLINE") (100 . "AcDbEntity") (8 . "PLANTS") (62 . 94) (370 . 13) (100 . "AcDbPolyline") (90 . 3) (70 . 0)
(43 . 0.0) (10 13401.2062217195 4004.5248868778) (10 13385.22239819 4019.614479638) (10 13374.8118778281
4053.5449095023))
((0 . "LWPOLYLINE") (100 . "AcDbEntity") (8 . "PLANTS") (62 . 94) (370 . 13) (100 . "AcDbPolyline") (90 . 2) (70 . 0)
(43 . 0.0) (10 13393.665158371 4061.0859728507) (10 13374.8118778281 4053.5449095023))
((0 . "LWPOLYLINE") (100 . "AcDbEntity") (8 . "PLANTS") (62 . 94) (370 . 13) (100 . "AcDbPolyline") (90 . 3) (70 . 0)
(43 . 0.0) (10 13374.8118778281 3996.9838235294) (10 13378.7364253394 3990.6331447964) (10 13395.5501131222
3985.6716063348))
((0 . "LWPOLYLINE") (100 . "AcDbEntity") (8 . "PLANTS") (62 . 94) (370 . 13) (100 . "AcDbPolyline") (90 . 3) (70 . 0)
(43 . 0.0) (10 13374.8118778281 3857.4660633484) (10 13390.0430995475 3831.0704751131) (10 13408.7485294118
3815.9883484163))
((0 . "LWPOLYLINE") (100 . "AcDbEntity") (8 . "PLANTS") (62 . 94) (370 . 13) (100 . "AcDbPolyline") (90 . 2) (70 . 0)
(43 . 0.0) (10 13374.8118778281 3857.4660633484) (10 13389.8940045249 3868.778280543))
((0 . "LWPOLYLINE") (100 . "AcDbEntity") (8 . "PLANTS") (62 . 94) (370 . 13) (100 . "AcDbPolyline") (90 . 3) (70 . 0)
(43 . 0.0) (10 13404.9908371041 3732.8835972851) (10 13453.99739819 3732.8835972851) (10 13465.3096153846
3729.260520362))
((0 . "LWPOLYLINE") (100 . "AcDbEntity") (8 . "PLANTS") (62 . 94) (370 . 13) (100 . "AcDbPolyline") (90 . 2) (70 . 0)
(43 . 0.0) (10 13378.5817873303 935.1442307692) (10 13378.5817873303 904.9773755656))
((0 . "LWPOLYLINE") (100 . "AcDbEntity") (8 . "PLANTS") (62 . 94) (370 . 13) (100 . "AcDbPolyline") (90 . 3) (70 . 0)
(43 . 0.0) (10 13378.5817873303 935.1442307692) (10 13388.8444570136 953.996040724) (10 13389.8940045249
969.0808823529))
((0 . "LWPOLYLINE") (100 . "AcDbEntity") (8 . "PLANTS") (62 . 94) (370 . 13) (100 . "AcDbPolyline") (90 . 2) (70 . 0)
(43 . 0.0) (10 13423.8306561086 904.9773755656) (10 13378.5817873303 904.9773755656))
((0 . "LWPOLYLINE") (100 . "AcDbEntity") (8 . "PLANTS") (62 . 94) (370 . 13) (100 . "AcDbPolyline") (90 . 3) (70 . 0)
(43 . 0.0) (10 13378.5817873303 241.3263574661) (10 13389.8940045249 237.7042986425) (10 13442.6851809955
237.556561086))
((0 . "LWPOLYLINE") (100 . "AcDbEntity") (8 . "PLANTS") (62 . 94) (370 . 13) (100 . "AcDbPolyline") (90 . 3) (70 . 0)
(43 . 0.0) (10 13404.9773755656 279.0356334842) (10 13387.1805429864 263.8037330317) (10 13378.5817873303
241.3263574661))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13395.5524944014 6730.7692307692 0.0) (10 13422.1694852116 6732.1797049722 0.0) (10 13432.5394533597
6758.1798063027 0.0) (10 13431.3729638009 6779.7885746606 0.0))
((0 . "LWPOLYLINE") (100 . "AcDbEntity") (8 . "PLANTS") (62 . 94) (370 . 13) (100 . "AcDbPolyline") (90 . 3) (70 . 0)
(43 . 0.0) (10 13382.3529411765 395.92760181) (10 13391.0980769231 346.9089366516) (10 13404.9773755656 335.596719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13382.3529411765 395.92760181 0.0) (10 13430.5444239122 404.6208231151 0.0) (10 13438.7154652298
460.1921639654 0.0) (10 13470.2427469422 491.2093425082 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13389.8940045249 6836.3496606335 0.0) (10 13405.3152656848 6805.6625752095 0.0) (10 13446.4156327079
6834.8893740331 0.0) (10 13469.0795248869 6813.7252262443 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7735801506) (40
. 1) (40 . 1) (40 . 1) (40 . 1) (10 13389.8940045249 6836.3496606335 0.0) (10 13414.9840917227 6848.3587178639 0.0) (10
13503.9644773476 6877.7982939154 0.0) (10 13519.2376648028 6835.4127859559 0.0) (10 13514.3283936652 6821.2669683258
0.0))
((0 . "LWPOLYLINE") (100 . "AcDbEntity") (8 . "PLANTS") (62 . 94) (370 . 13) (100 . "AcDbPolyline") (90 . 2) (70 . 0)
(43 . 0.0) (10 13401.2062217195 995.4751131222) (10 13389.8940045249 969.0808823529))
((0 . "LWPOLYLINE") (100 . "AcDbEntity") (8 . "PLANTS") (62 . 94) (370 . 13) (100 . "AcDbPolyline") (90 . 2) (70 . 0)
(43 . 0.0) (10 13393.665158371 4061.0859728507) (10 13416.2895927602 4053.5449095023))
((0 . "LWPOLYLINE") (100 . "AcDbEntity") (8 . "PLANTS") (62 . 94) (370 . 13) (100 . "AcDbPolyline") (90 . 2) (70 . 0)
(43 . 0.0) (10 13403.0924208145 3964.9321266968) (10 13395.5501131222 3985.6716063348))
((0 . "LWPOLYLINE") (100 . "AcDbEntity") (8 . "PLANTS") (62 . 94) (370 . 13) (100 . "AcDbPolyline") (90 . 3) (70 . 0)
(43 . 0.0) (10 13401.2062217195 3993.2126696833) (10 13393.665158371 3989.4415158371) (10 13395.5501131222
3985.6716063348))
((0 . "LWPOLYLINE") (100 . "AcDbEntity") (8 . "PLANTS") (62 . 94) (370 . 13) (100 . "AcDbPolyline") (90 . 2) (70 . 0)
(43 . 0.0) (10 13401.2062217195 3993.2126696833) (10 13395.5501131222 3985.6716063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13401.2062217195 4147.8125565611 0.0) (10 13425.2216723359 4183.8686197805 0.0) (10 13390.0968938141
4215.8229619005 0.0) (10 13398.6538374334 4250.4004577209 0.0))
((0 . "LWPOLYLINE") (100 . "AcDbEntity") (8 . "PLANTS") (62 . 94) (370 . 13) (100 . "AcDbPolyline") (90 . 3) (70 . 0)
(43 . 0.0) (10 13401.2062217195 4147.8125565611) (10 13424.8800904977 4095.0226244344) (10 13442.6851809955
4072.3981900452))
((0 . "LWPOLYLINE") (100 . "AcDbEntity") (8 . "PLANTS") (62 . 94) (370 . 13) (100 . "AcDbPolyline") (90 . 2) (70 . 0)
(43 . 0.0) (10 13401.2062217195 4004.5248868778) (10 13401.2062217195 3993.2126696833))
((0 . "LWPOLYLINE") (100 . "AcDbEntity") (8 . "PLANTS") (62 . 94) (370 . 13) (100 . "AcDbPolyline") (90 . 3) (70 . 0)
(43 . 0.0) (10 13401.2062217195 4004.5248868778) (10 13416.2895927602 4007.2393665158) (10 13461.5384615385
3989.4415158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13504.9023755656 3915.9121040723 0.0) (10 13470.0450627382 3891.0931089332 0.0) (10 13422.2879745321
3926.1738319803 0.0) (10 13401.2062217195 3955.5048642534 0.0))
((0 . "LWPOLYLINE") (100 . "AcDbEntity") (8 . "PLANTS") (62 . 94) (370 . 13) (100 . "AcDbPolyline") (90 . 2) (70 . 0)
(43 . 0.0) (10 13401.2062217195 3955.5048642534) (10 13403.0924208145 3964.9321266968))
((0 . "LWPOLYLINE") (100 . "AcDbEntity") (8 . "PLANTS") (62 . 94) (370 . 13) (100 . "AcDbPolyline") (90 . 2) (70 . 0)
(43 . 0.0) (10 13401.2062217195 995.4751131222) (10 13416.2895927602 999.2449095023))
((0 . "LWPOLYLINE") (100 . "AcDbEntity") (8 . "PLANTS") (62 . 94) (370 . 13) (100 . "AcDbPolyline") (90 . 3) (70 . 0)
(43 . 0.0) (10 13403.0924208145 3964.9321266968) (10 13408.7485294118 3963.0471719457) (10 13412.518438914
3970.5882352941))
((0 . "LWPOLYLINE") (100 . "AcDbEntity") (8 . "PLANTS") (62 . 94) (370 . 13) (100 . "AcDbPolyline") (90 . 2) (70 . 0)
(43 . 0.0) (10 13403.0924208145 3964.9321266968) (10 13412.518438914 3970.5882352941))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.265334884) (40 .
1) (40 . 1) (40 . 1) (40 . 1) (10 13404.9773755656 1168.9281674209 0.0) (10 13384.7309818789 1179.2249658283 0.0) (10
13377.850721088 1134.3237097202 0.0) (10 13422.5836283413 1084.2325220678 0.0) (10 13457.7673076923 1089.7426470588
0.0))
((0 . "LWPOLYLINE") (100 . "AcDbEntity") (8 . "PLANTS") (62 . 94) (370 . 13) (100 . "AcDbPolyline") (90 . 3) (70 . 0)
(43 . 0.0) (10 13404.9773755656 279.0356334842) (10 13401.5016968326 320.5118778281) (10 13404.9773755656
335.596719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13469.0795248869 328.0542986425 0.0) (10 13449.773252796 338.1845433092 0.0) (10 13426.0663705733
343.2148961381 0.0) (10 13404.9773755656 335.596719457 0.0))
((0 . "LWPOLYLINE") (100 . "AcDbEntity") (8 . "PLANTS") (62 . 94) (370 . 13) (100 . "AcDbPolyline") (90 . 2) (70 . 0)
(43 . 0.0) (10 13442.6851809955 271.4932126697) (10 13404.9773755656 279.0356334842))
((0 . "LWPOLYLINE") (100 . "AcDbEntity") (8 . "PLANTS") (62 . 94) (370 . 13) (100 . "AcDbPolyline") (90 . 2) (70 . 0)
(43 . 0.0) (10 13408.7485294118 3815.9883484163) (10 13408.7485294118 3808.446040724))
((0 . "LWPOLYLINE") (100 . "AcDbEntity") (8 . "PLANTS") (62 . 94) (370 . 13) (100 . "AcDbPolyline") (90 . 3) (70 . 0)
(43 . 0.0) (10 13438.9140271493 3865.0071266968) (10 13437.709841629 3838.6190045249) (10 13408.7485294118
3815.9883484163))
((0 . "LWPOLYLINE") (100 . "AcDbEntity") (8 . "PLANTS") (62 . 94) (370 . 13) (100 . "AcDbPolyline") (90 . 3) (70 . 0)
(43 . 0.0) (10 13457.7673076923 3800.9049773756) (10 13420.0607466063 3801.0596153846) (10 13408.7485294118
3808.446040724))
((0 . "LWPOLYLINE") (100 . "AcDbEntity") (8 . "PLANTS") (62 . 94) (370 . 13) (100 . "AcDbPolyline") (90 . 2) (70 . 0)
(43 . 0.0) (10 13416.2895927602 4053.5449095023) (10 13412.518438914 4038.4615384615))
((0 . "LWPOLYLINE") (100 . "AcDbEntity") (8 . "PLANTS") (62 . 94) (370 . 13) (100 . "AcDbPolyline") (90 . 3) (70 . 0)
(43 . 0.0) (10 13461.5384615385 3978.1292986425) (10 13435.1428733032 3968.0149321267) (10 13412.518438914
3970.5882352941))
((0 . "LWPOLYLINE") (100 . "AcDbEntity") (8 . "PLANTS") (62 . 94) (370 . 13) (100 . "AcDbPolyline") (90 . 2) (70 . 0)
(43 . 0.0) (10 13416.2895927602 4053.5449095023) (10 13442.6851809955 4057.3148190045))
((0 . "LWPOLYLINE") (100 . "AcDbEntity") (8 . "PLANTS") (62 . 94) (370 . 13) (100 . "AcDbPolyline") (90 . 3) (70 . 0)
(43 . 0.0) (10 13446.4550904977 999.2449095023) (10 13431.3729638009 995.4751131222) (10 13416.2895927602
999.2449095023))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13480.3917420814 912.5197963801 0.0) (10 13469.2551612126 893.5398168826 0.0) (10 13439.0033076275
889.1244208289 0.0) (10 13423.8306561086 904.9773755656 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13480.3917420814 912.5197963801 0.0) (10 13472.9469587479 938.5450837053 0.0) (10 13423.3670115657
932.8759372448 0.0) (10 13423.8306561086 904.9773755656 0.0))
((0 . "LWPOLYLINE") (100 . "AcDbEntity") (8 . "PLANTS") (62 . 94) (370 . 13) (100 . "AcDbPolyline") (90 . 3) (70 . 0)
(43 . 0.0) (10 13457.7673076923 1150.0763574661) (10 13438.9140271493 1151.2797511312) (10 13427.6018099548
1161.3885746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13469.0795248869 6813.7252262443 0.0) (10 13482.2912531106 6787.1194673495 0.0) (10 13451.9528271512
6772.2775597231 0.0) (10 13431.3729638009 6779.7885746606 0.0))
((0 . "LWPOLYLINE") (100 . "AcDbEntity") (8 . "PLANTS") (62 . 94) (370 . 13) (100 . "AcDbPolyline") (90 . 2) (70 . 0)
(43 . 0.0) (10 13438.9140271493 972.850678733) (10 13431.3729638009 961.5384615385))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13476.6218325792 328.0542986425 0.0) (10 13478.7428233004 354.0296903978 0.0) (10 13461.1332832729
385.3430463793 0.0) (10 13435.1428733032 392.1578054299 0.0))
((0 . "LWPOLYLINE") (100 . "AcDbEntity") (8 . "PLANTS") (62 . 94) (370 . 13) (100 . "AcDbPolyline") (90 . 3) (70 . 0)
(43 . 0.0) (10 13438.9140271493 3865.0071266968) (10 13453.99739819 3863.9510180995) (10 13480.3917420814
3846.1538461538))
((0 . "LWPOLYLINE") (100 . "AcDbEntity") (8 . "PLANTS") (62 . 94) (370 . 13) (100 . "AcDbPolyline") (90 . 2) (70 . 0)
(43 . 0.0) (10 13442.6851809955 4057.3148190045) (10 13442.6851809955 4072.3981900452))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13454.1452488687 4217.1056108597 0.0) (10 13452.9414877922 4170.4252191254 0.0) (10 13480.1747548679
4112.2866469451 0.0) (10 13442.6851809955 4072.3981900452 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13461.5384615385 3989.4415158371 0.0) (10 13470.7841512064 4012.4847549308 0.0) (10 13463.1879558913
4042.7189888817 0.0) (10 13442.6851809955 4057.3148190045 0.0))
((0 . "LWPOLYLINE") (100 . "AcDbEntity") (8 . "PLANTS") (62 . 94) (370 . 13) (100 . "AcDbPolyline") (90 . 3) (70 . 0)
(43 . 0.0) (10 13442.6851809955 271.4932126697) (10 13476.6218325792 266.5247737557) (10 13491.703959276
248.8687782805))
((0 . "LWPOLYLINE") (100 . "AcDbEntity") (8 . "PLANTS") (62 . 94) (370 . 13) (100 . "AcDbPolyline") (90 . 2) (70 . 0)
(43 . 0.0) (10 13442.6851809955 271.4932126697) (10 13442.6851809955 237.556561086))
((0 . "LWPOLYLINE") (100 . "AcDbEntity") (8 . "PLANTS") (62 . 94) (370 . 13) (100 . "AcDbPolyline") (90 . 3) (70 . 0)
(43 . 0.0) (10 13442.6851809955 271.4932126697) (10 13447.6522624434 294.1176470588) (10 13469.0795248869
328.0542986425))
((0 . "LWPOLYLINE") (100 . "AcDbEntity") (8 . "PLANTS") (62 . 94) (370 . 13) (100 . "AcDbPolyline") (90 . 3) (70 . 0)
(43 . 0.0) (10 13491.703959276 248.8687782805) (10 13476.6218325792 237.711199095) (10 13442.6851809955 237.556561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13446.4550904977 999.2449095023 0.0) (10 13454.5921534576 983.5986856052 0.0) (10 13470.515314168
971.9775242981 0.0) (10 13487.9340497738 969.0808823529 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13446.4550904977 999.2449095022 0.0) (10 13454.5295760552 1022.9240782995 0.0) (10 13485.4255372474
1030.2358879011 0.0) (10 13503.0161764706 1012.443438914 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4430579125) (40
. 1) (40 . 1) (40 . 1) (40 . 1) (10 13563.3484162896 3808.446040724 0.0) (10 13549.9974088176 3794.2920895172 0.0) (10
13514.7031516044 3796.9918208959 0.0) (10 13475.9615258739 3791.1884042595 0.0) (10 13457.7673076923 3800.9049773755
0.0))
((0 . "LWPOLYLINE") (100 . "AcDbEntity") (8 . "PLANTS") (62 . 94) (370 . 13) (100 . "AcDbPolyline") (90 . 2) (70 . 0)
(43 . 0.0) (10 13457.7673076923 3800.9049773756) (10 13480.3917420814 3846.1538461538))
((0 . "LWPOLYLINE") (100 . "AcDbEntity") (8 . "PLANTS") (62 . 94) (370 . 13) (100 . "AcDbPolyline") (90 . 2) (70 . 0)
(43 . 0.0) (10 13457.7673076923 1150.0763574661) (10 13476.6218325792 1146.3037330317))
((0 . "LWPOLYLINE") (100 . "AcDbEntity") (8 . "PLANTS") (62 . 94) (370 . 13) (100 . "AcDbPolyline") (90 . 2) (70 . 0)
(43 . 0.0) (10 13457.7673076923 1150.0763574661) (10 13457.7673076923 1089.7426470588))
((0 . "LWPOLYLINE") (100 . "AcDbEntity") (8 . "PLANTS") (62 . 94) (370 . 13) (100 . "AcDbPolyline") (90 . 2) (70 . 0)
(43 . 0.0) (10 13457.7673076923 1150.0763574661) (10 13457.7773588372 1218.94659665))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13503.0161764706 1012.443438914 0.0) (10 13525.2293855111 1061.858361131 0.0) (10 13474.1607495907
1063.6729599543 0.0) (10 13457.7673076923 1089.7426470588 0.0))
((0 . "LWPOLYLINE") (100 . "AcDbEntity") (8 . "PLANTS") (62 . 94) (370 . 13) (100 . "AcDbPolyline") (90 . 2) (70 . 0)
(43 . 0.0) (10 13461.5384615385 3978.1292986425) (10 13461.5384615385 3989.4415158371))
((0 . "LWPOLYLINE") (100 . "AcDbEntity") (8 . "PLANTS") (62 . 94) (370 . 13) (100 . "AcDbPolyline") (90 . 3) (70 . 0)
(43 . 0.0) (10 13504.9023755656 3915.9121040724) (10 13485.2192307692 3936.6515837104) (10 13461.5384615385
3978.1292986425))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13510.5584841629 328.0542986425 0.0) (10 13541.3334662082 360.9518221326 0.0) (10 13498.5791588685
416.3427341389 0.0) (10 13465.3096153847 422.3218325794 0.0))
((0 . "LWPOLYLINE") (100 . "AcDbEntity") (8 . "PLANTS") (62 . 94) (370 . 13) (100 . "AcDbPolyline") (90 . 3) (70 . 0)
(43 . 0.0) (10 13469.0795248869 6813.7252262443) (10 13476.6287330317 6819.9212669683) (10 13495.4751131222
6817.4964932127))
((0 . "LWPOLYLINE") (100 . "AcDbEntity") (8 . "PLANTS") (62 . 94) (370 . 13) (100 . "AcDbPolyline") (90 . 2) (70 . 0)
(43 . 0.0) (10 13476.6218325792 328.0542986425) (10 13469.0795248869 328.0542986425))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13525.6406108597 4147.8125565611 0.0) (10 13504.0323295762 4150.2879591869 0.0) (10 13501.4461903519
4176.1704202813 0.0) (10 13496.7384454777 4191.5496928944 0.0))
((0 . "LWPOLYLINE") (100 . "AcDbEntity") (8 . "PLANTS") (62 . 94) (370 . 13) (100 . "AcDbPolyline") (90 . 2) (70 . 0)
(43 . 0.0) (10 13476.6218325792 328.0542986425) (10 13510.5584841629 328.0542986425))
((0 . "LWPOLYLINE") (100 . "AcDbEntity") (8 . "PLANTS") (62 . 94) (370 . 13) (100 . "AcDbPolyline") (90 . 3) (70 . 0)
(43 . 0.0) (10 13510.5584841629 3868.778280543) (10 13495.4751131222 3853.8498868778) (10 13480.3917420814
3846.1538461538))
((0 . "LWPOLYLINE") (100 . "AcDbEntity") (8 . "PLANTS") (62 . 94) (370 . 13) (100 . "AcDbPolyline") (90 . 3) (70 . 0)
(43 . 0.0) (10 13480.3917420814 912.5197963801) (10 13506.7804298643 912.6668552036) (10 13514.3283936652
916.2895927602))
((0 . "LWPOLYLINE") (100 . "AcDbEntity") (8 . "PLANTS") (62 . 94) (370 . 13) (100 . "AcDbPolyline") (90 . 2) (70 . 0)
(43 . 0.0) (10 13514.3283936652 916.2895927602) (10 13487.9340497738 969.0808823529))
((0 . "LWPOLYLINE") (100 . "AcDbEntity") (8 . "PLANTS") (62 . 94) (370 . 13) (100 . "AcDbPolyline") (90 . 3) (70 . 0)
(43 . 0.0) (10 13503.0161764706 1012.443438914) (10 13494.2779411765 976.6280542986) (10 13487.9340497738
969.0808823529))
((0 . "LWPOLYLINE") (100 . "AcDbEntity") (8 . "PLANTS") (62 . 94) (370 . 13) (100 . "AcDbPolyline") (90 . 2) (70 . 0)
(43 . 0.0) (10 13491.703959276 248.8687782805) (10 13499.2462669683 248.8687782805))
((0 . "LWPOLYLINE") (100 . "AcDbEntity") (8 . "PLANTS") (62 . 94) (370 . 13) (100 . "AcDbPolyline") (90 . 3) (70 . 0)
(43 . 0.0) (10 13536.9528280543 1085.9728506787) (10 13514.4830316742 1104.8274886878) (10 13499.2462669683
1127.4519230769))
((0 . "LWPOLYLINE") (100 . "AcDbEntity") (8 . "PLANTS") (62 . 94) (370 . 13) (100 . "AcDbPolyline") (90 . 2) (70 . 0)
(43 . 0.0) (10 13499.2462669683 263.9507918552) (10 13499.2462669683 248.8687782805))
((0 . "LWPOLYLINE") (100 . "AcDbEntity") (8 . "PLANTS") (62 . 94) (370 . 13) (100 . "AcDbPolyline") (90 . 2) (70 . 0)
(43 . 0.0) (10 13548.2650452489 248.8687782805) (10 13499.2462669683 248.8687782805))
((0 . "LWPOLYLINE") (100 . "AcDbEntity") (8 . "PLANTS") (62 . 94) (370 . 13) (100 . "AcDbPolyline") (90 . 3) (70 . 0)
(43 . 0.0) (10 13540.7239819005 3691.553959276) (10 13531.9843891403 3657.765158371) (10 13503.0161764706
3631.221719457))
((0 . "LWPOLYLINE") (100 . "AcDbEntity") (8 . "PLANTS") (62 . 94) (370 . 13) (100 . "AcDbPolyline") (90 . 2) (70 . 0)
(43 . 0.0) (10 13511.2071897491 3238.920448531) (10 13536.9528280543 3239.0645927602))
((0 . "LWPOLYLINE") (100 . "AcDbEntity") (8 . "PLANTS") (62 . 94) (370 . 13) (100 . "AcDbPolyline") (90 . 2) (70 . 0)
(43 . 0.0) (10 13521.8702488688 1187.7828054299) (10 13503.0161764706 1187.7828054299))
((0 . "LWPOLYLINE") (100 . "AcDbEntity") (8 . "PLANTS") (62 . 94) (370 . 13) (100 . "AcDbPolyline") (90 . 2) (70 . 0)
(43 . 0.0) (10 13503.0161764706 1012.443438914) (10 13544.4951357466 1010.5571266968))
((0 . "LWPOLYLINE") (100 . "AcDbEntity") (8 . "PLANTS") (62 . 94) (370 . 13) (100 . "AcDbPolyline") (90 . 3) (70 . 0)
(43 . 0.0) (10 13504.9023755656 3915.9121040724) (10 13510.4066742081 3902.7179864253) (10 13510.5584841629
3868.778280543))
((0 . "LWPOLYLINE") (100 . "AcDbEntity") (8 . "PLANTS") (62 . 94) (370 . 13) (100 . "AcDbPolyline") (90 . 3) (70 . 0)
(43 . 0.0) (10 13504.9023755656 3915.9121040724) (10 13521.7160633484 3932.8804298643) (10 13525.6406108597
3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13544.4951357466 3623.6806561086 0.0) (10 13537.2630997239 3607.2133578719 0.0) (10 13512.3055633532
3614.0073930205 0.0) (10 13506.7873303167 3597.2850678733 0.0))
((0 . "LWPOLYLINE") (100 . "AcDbEntity") (8 . "PLANTS") (62 . 94) (370 . 13) (100 . "AcDbPolyline") (90 . 2) (70 . 0)
(43 . 0.0) (10 13540.7239819005 3868.778280543) (10 13510.5584841629 3868.778280543))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13510.5584841629 328.0542986425 0.0) (10 13516.8372943249 305.0861991356 0.0) (10 13544.2497286536
315.1495036679 0.0) (10 13555.8073529412 297.8874434389 0.0))
((0 . "LWPOLYLINE") (100 . "AcDbEntity") (8 . "PLANTS") (62 . 94) (370 . 13) (100 . "AcDbPolyline") (90 . 3) (70 . 0)
(43 . 0.0) (10 13514.3283936652 3751.8849547511) (10 13525.6406108597 3761.9933257919) (10 13552.036199095
3763.1971719457))
((0 . "LWPOLYLINE") (100 . "AcDbEntity") (8 . "PLANTS") (62 . 94) (370 . 13) (100 . "AcDbPolyline") (90 . 2) (70 . 0)
(43 . 0.0) (10 13514.3283936652 916.2895927602) (10 13533.182918552 920.0593891403))
((0 . "LWPOLYLINE") (100 . "AcDbEntity") (8 . "PLANTS") (62 . 94) (370 . 13) (100 . "AcDbPolyline") (90 . 2) (70 . 0)
(43 . 0.0) (10 13540.7239819005 3733.0316742081) (10 13518.0995475113 3725.4906108597))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13521.8702488688 1187.7828054299 0.0) (10 13521.8702488688 1210.539539176 0.0) (10 13521.8702488688
1233.2962729221 0.0) (10 13521.8702488688 1256.0530066683 0.0))
((0 . "LWPOLYLINE") (100 . "AcDbEntity") (8 . "PLANTS") (62 . 94) (370 . 13) (100 . "AcDbPolyline") (90 . 3) (70 . 0)
(43 . 0.0) (10 13521.8702488688 1187.7828054299) (10 13523.0748868778 1153.8523755656) (10 13548.2650452489
1138.7641402715))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13521.8707013575 3548.2657239819 0.0) (10 13538.9385967895 3566.5958486243 0.0) (10 13561.1802412863
3590.0533268029 0.0) (10 13589.7440045249 3582.2023755656 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5243198851) (40
. 1) (40 . 1) (40 . 1) (40 . 1) (10 13525.6406108596 3944.1926470588 0.0) (10 13507.3653557568 3976.613170031 0.0) (10
13525.2309803977 4046.8446560484 0.0) (10 13522.1216233611 4115.8517165339 0.0) (10 13525.6406108596 4147.8125565611
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13525.6406108597 4147.8125565611 0.0) (10 13553.8107964735 4172.5016430986 0.0) (10 13551.9594578308
4215.3549183727 0.0) (10 13552.0293281072 4251.3269042316 0.0))
((0 . "LWPOLYLINE") (100 . "AcDbEntity") (8 . "PLANTS") (62 . 94) (370 . 13) (100 . "AcDbPolyline") (90 . 3) (70 . 0)
(43 . 0.0) (10 13525.6406108597 3944.1926470588) (10 13547.067760181 3959.282239819) (10 13559.5772624434
3993.2126696833))
((0 . "LWPOLYLINE") (100 . "AcDbEntity") (8 . "PLANTS") (62 . 94) (370 . 13) (100 . "AcDbPolyline") (90 . 2) (70 . 0)
(43 . 0.0) (10 13533.182918552 3695.3238687783) (10 13540.7239819005 3691.553959276))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5661426261) (40
. 1) (40 . 1) (40 . 1) (40 . 1) (10 13661.3872171946 912.51979638 0.0) (10 13642.388507962 893.0022649904 0.0) (10
13591.3502228328 893.4678057137 0.0) (10 13543.2302898185 900.8586900725 0.0) (10 13533.182918552 920.0593891402 0.0))
((0 . "LWPOLYLINE") (100 . "AcDbEntity") (8 . "PLANTS") (62 . 94) (370 . 13) (100 . "AcDbPolyline") (90 . 2) (70 . 0)
(43 . 0.0) (10 13540.7239819005 931.3716063348) (10 13533.182918552 920.0593891403))
((0 . "LWPOLYLINE") (100 . "AcDbEntity") (8 . "PLANTS") (62 . 94) (370 . 13) (100 . "AcDbPolyline") (90 . 2) (70 . 0)
(43 . 0.0) (10 13536.9405080269 3235.2941176471) (10 13536.9528280543 3239.0645927602))
((0 . "LWPOLYLINE") (100 . "AcDbEntity") (8 . "PLANTS") (62 . 94) (370 . 13) (100 . "AcDbPolyline") (90 . 3) (70 . 0)
(43 . 0.0) (10 13574.6606334842 3239.0645927602) (10 13559.5772624434 3242.8358597285) (10 13536.9528280543
3239.0645927602))
((0 . "LWPOLYLINE") (100 . "AcDbEntity") (8 . "PLANTS") (62 . 94) (370 . 13) (100 . "AcDbPolyline") (90 . 3) (70 . 0)
(43 . 0.0) (10 13536.9528280543 1085.9728506787) (10 13536.9528280543 1078.4304298643) (10 13544.4951357466
1074.6606334842))
((0 . "LWPOLYLINE") (100 . "AcDbEntity") (8 . "PLANTS") (62 . 94) (370 . 13) (100 . "AcDbPolyline") (90 . 3) (70 . 0)
(43 . 0.0) (10 13536.9528280543 1085.9728506787) (10 13544.3404977376 1097.2850678733) (10 13548.2650452489
1138.7641402715))
((0 . "LWPOLYLINE") (100 . "AcDbEntity") (8 . "PLANTS") (62 . 94) (370 . 13) (100 . "AcDbPolyline") (90 . 3) (70 . 0)
(43 . 0.0) (10 13540.7239819005 3868.778280543) (10 13553.0925339367 3838.6190045249) (10 13563.3484162896
3831.0704751131))
((0 . "LWPOLYLINE") (100 . "AcDbEntity") (8 . "PLANTS") (62 . 94) (370 . 13) (100 . "AcDbPolyline") (90 . 2) (70 . 0)
(43 . 0.0) (10 13563.3484162896 3876.3193438914) (10 13540.7239819005 3868.778280543))
((0 . "LWPOLYLINE") (100 . "AcDbEntity") (8 . "PLANTS") (62 . 94) (370 . 13) (100 . "AcDbPolyline") (90 . 2) (70 . 0)
(43 . 0.0) (10 13548.2650452489 3695.3238687783) (10 13540.7239819005 3691.553959276))
((0 . "LWPOLYLINE") (100 . "AcDbEntity") (8 . "PLANTS") (62 . 94) (370 . 13) (100 . "AcDbPolyline") (90 . 2) (70 . 0)
(43 . 0.0) (10 13540.7239819005 931.3716063348) (10 13544.4951357466 1010.5571266968))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13540.7239819005 931.3716063348 0.0) (10 13566.7999366621 918.1334135489 0.0) (10 13580.9752565399
949.3576282502 0.0) (10 13604.8261312217 946.4564479638 0.0))
((0 . "LWPOLYLINE") (100 . "AcDbEntity") (8 . "PLANTS") (62 . 94) (370 . 13) (100 . "AcDbPolyline") (90 . 2) (70 . 0)
(43 . 0.0) (10 13544.4951357466 1074.6606334842) (10 13544.4951357466 1010.5571266968))
((0 . "LWPOLYLINE") (100 . "AcDbEntity") (8 . "PLANTS") (62 . 94) (370 . 13) (100 . "AcDbPolyline") (90 . 3) (70 . 0)
(43 . 0.0) (10 13601.0562217195 1116.1397058824) (10 13574.6606334842 1082.3563348416) (10 13544.4951357466
1074.6606334842))
((0 . "LWPOLYLINE") (100 . "AcDbEntity") (8 . "PLANTS") (62 . 94) (370 . 13) (100 . "AcDbPolyline") (90 . 2) (70 . 0)
(43 . 0.0) (10 13544.4951357466 1010.5571266968) (10 13601.0562217195 1018.0995475113))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13548.2650452488 3695.3238687783 0.0) (10 13576.2226355392 3660.7962077196 0.0) (10 13629.9157933567
3742.4369090455 0.0) (10 13589.7440045249 3751.8849547513 0.0))
((0 . "LWPOLYLINE") (100 . "AcDbEntity") (8 . "PLANTS") (62 . 94) (370 . 13) (100 . "AcDbPolyline") (90 . 3) (70 . 0)
(43 . 0.0) (10 13548.2650452489 3695.3238687783) (10 13555.9621040724 3710.407239819) (10 13589.7440045249
3751.8849547511))
((0 . "LWPOLYLINE") (100 . "AcDbEntity") (8 . "PLANTS") (62 . 94) (370 . 13) (100 . "AcDbPolyline") (90 . 2) (70 . 0)
(43 . 0.0) (10 13559.5772624434 1153.8461538462) (10 13548.2650452489 1138.7641402715))
((0 . "LWPOLYLINE") (100 . "AcDbEntity") (8 . "PLANTS") (62 . 94) (370 . 13) (100 . "AcDbPolyline") (90 . 2) (70 . 0)
(43 . 0.0) (10 13702.8658371041 561.840158371) (10 13719.4569230769 561.840158371))
((0 . "LWPOLYLINE") (100 . "AcDbEntity") (8 . "PLANTS") (62 . 94) (370 . 13) (100 . "AcDbPolyline") (90 . 2) (70 . 0)
(43 . 0.0) (10 14233.4088348416 561.840158371) (10 14252.0223879062 561.840158371))
((0 . "LWPOLYLINE") (100 . "AcDbEntity") (8 . "PLANTS") (62 . 94) (370 . 13) (100 . "AcDbPolyline") (90 . 2) (70 . 0)
(43 . 0.0) (10 15317.9584898892 565.2459718606) (10 15367.4789468082 565.4225369804))
((0 . "LWPOLYLINE") (100 . "AcDbEntity") (8 . "PLANTS") (62 . 94) (370 . 13) (100 . "AcDbPolyline") (90 . 3) (70 . 0)
(43 . 0.0) (10 13616.1383484163 241.3263574661) (10 13563.3484162896 237.711199095) (10 13548.2650452489
248.8687782805))
((0 . "LWPOLYLINE") (100 . "AcDbEntity") (8 . "PLANTS") (62 . 94) (370 . 13) (100 . "AcDbPolyline") (90 . 2) (70 . 0)
(43 . 0.0) (10 13548.2650452489 248.8687782805) (10 13555.8073529412 297.8874434389))
((0 . "LWPOLYLINE") (100 . "AcDbEntity") (8 . "PLANTS") (62 . 94) (370 . 13) (100 . "AcDbPolyline") (90 . 3) (70 . 0)
(43 . 0.0) (10 13567.1195701357 305.4298642534) (10 13553.2403846154 316.742081448) (10 13552.036199095 335.596719457))
((0 . "LWPOLYLINE") (100 . "AcDbEntity") (8 . "PLANTS") (62 . 94) (370 . 13) (100 . "AcDbPolyline") (90 . 3) (70 . 0)
(43 . 0.0) (10 13589.7440045249 3570.890158371) (10 13569.6990950226 3521.8700226244) (10 13555.8073529412
3499.2455882353))
((0 . "LWPOLYLINE") (100 . "AcDbEntity") (8 . "PLANTS") (62 . 94) (370 . 13) (100 . "AcDbPolyline") (90 . 2) (70 . 0)
(43 . 0.0) (10 13555.8073529412 3442.6845022624) (10 13563.3484162896 3465.3089366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13555.8069004525 1255.8545963325 0.0) (10 13558.5254189533 1221.9965007915 0.0) (10 13549.7431383926
1186.9997692171 0.0) (10 13559.5772624434 1153.8461538462 0.0))
((0 . "LWPOLYLINE") (100 . "AcDbEntity") (8 . "PLANTS") (62 . 94) (370 . 13) (100 . "AcDbPolyline") (90 . 3) (70 . 0)
(43 . 0.0) (10 13555.8073529412 358.2211538462) (10 13564.540158371 392.1578054299) (10 13574.6606334842
407.2398190045))
((0 . "LWPOLYLINE") (100 . "AcDbEntity") (8 . "PLANTS") (62 . 94) (370 . 13) (100 . "AcDbPolyline") (90 . 2) (70 . 0)
(43 . 0.0) (10 13567.1195701357 297.8874434389) (10 13555.8073529412 297.8874434389))
((0 . "LWPOLYLINE") (100 . "AcDbEntity") (8 . "PLANTS") (62 . 94) (370 . 13) (100 . "AcDbPolyline") (90 . 2) (70 . 0)
(43 . 0.0) (10 13608.5972850679 3993.2126696833) (10 13559.5772624434 3993.2126696833))
((0 . "LWPOLYLINE") (100 . "AcDbEntity") (8 . "PLANTS") (62 . 94) (370 . 13) (100 . "AcDbPolyline") (90 . 2) (70 . 0)
(43 . 0.0) (10 13567.1195701357 4038.4615384615) (10 13559.5772624434 3993.2126696833))
((0 . "LWPOLYLINE") (100 . "AcDbEntity") (8 . "PLANTS") (62 . 94) (370 . 13) (100 . "AcDbPolyline") (90 . 2) (70 . 0)
(43 . 0.0) (10 13559.5772624434 3472.850678733) (10 13563.3484162896 3465.3089366516))
((0 . "LWPOLYLINE") (100 . "AcDbEntity") (8 . "PLANTS") (62 . 94) (370 . 13) (100 . "AcDbPolyline") (90 . 3) (70 . 0)
(43 . 0.0) (10 13585.9728506787 1172.7007918552) (10 13578.2826923077 1162.4435520362) (10 13559.5772624434
1153.8461538462))
((0 . "LWPOLYLINE") (100 . "AcDbEntity") (8 . "PLANTS") (62 . 94) (370 . 13) (100 . "AcDbPolyline") (90 . 3) (70 . 0)
(43 . 0.0) (10 13563.3484162896 3876.3193438914) (10 13616.1383484163 3876.1653846154) (10 13631.221719457
3861.2372171946))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13614.2533936652 3955.5048642534 0.0) (10 13606.205962231 3919.8732311947 0.0) (10 13547.2290530367
3922.4356344091 0.0) (10 13563.3484162896 3876.3193438914 0.0))
((0 . "LWPOLYLINE") (100 . "AcDbEntity") (8 . "PLANTS") (62 . 94) (370 . 13) (100 . "AcDbPolyline") (90 . 2) (70 . 0)
(43 . 0.0) (10 13563.3484162896 3808.446040724) (10 13563.3484162896 3831.0704751131))
((0 . "LWPOLYLINE") (100 . "AcDbEntity") (8 . "PLANTS") (62 . 94) (370 . 13) (100 . "AcDbPolyline") (90 . 3) (70 . 0)
(43 . 0.0) (10 13627.4505656109 3842.3826923077) (10 13582.2016968326 3838.4643665158) (10 13563.3484162896
3831.0704751131))
((0 . "LWPOLYLINE") (100 . "AcDbEntity") (8 . "PLANTS") (62 . 94) (370 . 13) (100 . "AcDbPolyline") (90 . 3) (70 . 0)
(43 . 0.0) (10 13563.3484162896 3808.446040724) (10 13570.889479638 3800.9049773756) (10 13578.4317873303
3800.9049773756))
((0 . "LWPOLYLINE") (100 . "AcDbEntity") (8 . "PLANTS") (62 . 94) (370 . 13) (100 . "AcDbPolyline") (90 . 2) (70 . 0)
(43 . 0.0) (10 13604.8261312217 3495.4751131222) (10 13563.3484162896 3465.3089366516))
((0 . "SPLINE") (100 . "AcDbEntity") (8 . "PLANTS") (62 . 94) (370 . 13) (100 . "AcDbSpline") (70 . 0) (71 . 3) (72 .
13) (73 . 9) (74 . 0) (42 . 0.0000001) (43 . 0.0000001) (40 . 0.0) (40 . 0.0) (40 . 0.0) (40 . 0.0) (40 . 0.1126655905)
(40 . 0.2270587408) (40 . 0.2978174653) (40 . 0.55366251) (40 . 0.7576178651) (40 . 1) (40 . 1) (40 . 1) (40 . 1) (10
13627.4505656108 4291.1014705883 0.0) (10 13616.1072588631 4285.8370579526 0.0) (10 13608.0692226725 4269.7651433417
0.0) (10 13612.9757122394 4242.4518557535 0.0) (10 13613.3788997142 4202.6173756833 0.0) (10 13587.7522148202
4160.1778618028 0.0) (10 13568.5525088751 4099.7559403272 0.0) (10 13561.6454277083 4059.4245325745 0.0) (10
13567.1195701357 4038.4615384615 0.0))
((0 . "LWPOLYLINE") (100 . "AcDbEntity") (8 . "PLANTS") (62 . 94) (370 . 13) (100 . "AcDbPolyline") (90 . 3) (70 . 0)
(43 . 0.0) (10 13627.4505656109 4046.00260181) (10 13601.0562217195 4045.8547511312) (10 13567.1195701357
4038.4615384615))
((0 . "LWPOLYLINE") (100 . "AcDbEntity") (8 . "PLANTS") (62 . 94) (370 . 13) (100 . "AcDbPolyline") (90 . 3) (70 . 0)
(43 . 0.0) (10 13601.0562217195 444.9462669683) (10 13579.6290723982 456.4069004525) (10 13567.1195701357
486.4253393665))
((0 . "LWPOLYLINE") (100 . "AcDbEntity") (8 . "PLANTS") (62 . 94) (370 . 13) (100 . "AcDbPolyline") (90 . 2) (70 . 0)
(43 . 0.0) (10 13567.1195701357 305.4298642534) (10 13567.1195701357 297.8874434389))
((0 . "LWPOLYLINE") (100 . "AcDbEntity") (8 . "PLANTS") (62 . 94) (370 . 13) (100 . "AcDbPolyline") (90 . 2) (70 . 0)
(43 . 0.0) (10 13567.1195701357 305.4298642534) (10 13589.7440045249 324.2845022624))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13567.1195701358 297.8874434389 0.0) (10 13586.5100653809 267.4376644974 0.0) (10 13623.6783463563
309.1991155965 0.0) (10 13646.3050904977 279.0356334842 0.0))
((0 . "LWPOLYLINE") (100 . "AcDbEntity") (8 . "PLANTS") (62 . 94) (370 . 13) (100 . "AcDbPolyline") (90 . 2) (70 . 0)
(43 . 0.0) (10 13574.6606334842 3239.0645927602) (10 13574.6532470717 3235.2941176471))
((0 . "LWPOLYLINE") (100 . "AcDbEntity") (8 . "PLANTS") (62 . 94) (370 . 13) (100 . "AcDbPolyline") (90 . 3) (70 . 0)
(43 . 0.0) (10 15663.6481900453 1168.9281674208) (10 15667.4139140271 1180.2403846154) (10 15667.4139366734
1183.6187663614))
((0 . "LWPOLYLINE") (100 . "AcDbEntity") (8 . "PLANTS") (62 . 94) (370 . 13) (100 . "AcDbPolyline") (90 . 2) (70 . 0)
(43 . 0.0) (10 13604.8261312217 3239.0645927602) (10 13574.6606334842 3239.0645927602))
((0 . "LWPOLYLINE") (100 . "AcDbEntity") (8 . "PLANTS") (62 . 94) (370 . 13) (100 . "AcDbPolyline") (90 . 2) (70 . 0)
(43 . 0.0) (10 13585.9728506787 1172.7007918552) (10 13585.9703729365 1233.6288797653))
((0 . "LWPOLYLINE") (100 . "AcDbEntity") (8 . "PLANTS") (62 . 94) (370 . 13) (100 . "AcDbPolyline") (90 . 2) (70 . 0)
(43 . 0.0) (10 13578.4317873303 3800.9049773756) (10 13612.368438914 3800.9049773756))
((0 . "LWPOLYLINE") (100 . "AcDbEntity") (8 . "PLANTS") (62 . 94) (370 . 13) (100 . "AcDbPolyline") (90 . 3) (70 . 0)
(43 . 0.0) (10 13589.7440045249 3751.8849547511) (10 13582.3563348416 3763.1978506787) (10 13578.4317873303
3800.9049773756))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4376834883) (40
. 1) (40 . 1) (40 . 1) (40 . 1) (10 13578.4317873302 3665.1583710407 0.0) (10 13577.6501348928 3653.7633873644 0.0) (10
13597.6247399569 3628.7127948199 0.0) (10 13602.2412940646 3598.096836262 0.0) (10 13589.7440045248 3582.2023755656
0.0))
((0 . "LWPOLYLINE") (100 . "AcDbEntity") (8 . "PLANTS") (62 . 94) (370 . 13) (100 . "AcDbPolyline") (90 . 2) (70 . 0)
(43 . 0.0) (10 13585.9728506787 1172.7007918552) (10 13612.3679864253 1172.7007918552))
((0 . "LWPOLYLINE") (100 . "AcDbEntity") (8 . "PLANTS") (62 . 94) (370 . 13) (100 . "AcDbPolyline") (90 . 2) (70 . 0)
(43 . 0.0) (10 13589.7440045249 3570.890158371) (10 13589.7440045249 3582.2023755656))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.60169229) (40 .
1) (40 . 1) (40 . 1) (40 . 1) (10 13604.8261312217 3495.4751131222 0.0) (10 13583.9477001217 3517.2922083314 0.0) (10
13637.5030398293 3544.3436130068 0.0) (10 13604.3739561781 3568.8180397609 0.0) (10 13589.7440045248 3570.890158371
0.0))
((0 . "LWPOLYLINE") (100 . "AcDbEntity") (8 . "PLANTS") (62 . 94) (370 . 13) (100 . "AcDbPolyline") (90 . 3) (70 . 0)
(43 . 0.0) (10 13589.7440045249 324.2845022624) (10 13602.2535067873 384.6153846154) (10 13616.1383484163
407.2398190045))
((0 . "LWPOLYLINE") (100 . "AcDbEntity") (8 . "PLANTS") (62 . 94) (370 . 13) (100 . "AcDbPolyline") (90 . 2) (70 . 0)
(43 . 0.0) (10 13589.7440045249 324.2845022624) (10 13608.5972850679 328.0542986425))
((0 . "LWPOLYLINE") (100 . "AcDbEntity") (8 . "PLANTS") (62 . 94) (370 . 13) (100 . "AcDbPolyline") (90 . 2) (70 . 0)
(43 . 0.0) (10 13597.2850678733 3371.0407239819) (10 13593.5139140271 3359.7285067873))
((0 . "LWPOLYLINE") (100 . "AcDbEntity") (8 . "PLANTS") (62 . 94) (370 . 13) (100 . "AcDbPolyline") (90 . 3) (70 . 0)
(43 . 0.0) (10 13601.0562217195 1018.0995475113) (10 13611.1643665158 1006.7935520362) (10 13612.368438914
999.2449095023))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13601.0562217195 1018.0995475113 0.0) (10 13607.5266433161 1039.4039732414 0.0) (10 13617.8523443621
1077.7922622985 0.0) (10 13646.3050904977 1082.2030542986 0.0))
((0 . "LWPOLYLINE") (100 . "AcDbEntity") (8 . "PLANTS") (62 . 94) (370 . 13) (100 . "AcDbPolyline") (90 . 3) (70 . 0)
(43 . 0.0) (10 13601.0562217195 444.9462669683) (10 13602.1126696833 429.8642533937) (10 13616.1383484163
407.2398190045))
((0 . "LWPOLYLINE") (100 . "AcDbEntity") (8 . "PLANTS") (62 . 94) (370 . 13) (100 . "AcDbPolyline") (90 . 2) (70 . 0)
(43 . 0.0) (10 13601.0562217195 444.9462669683) (10 13627.4505656109 493.967760181))
((0 . "LWPOLYLINE") (100 . "AcDbEntity") (8 . "PLANTS") (62 . 94) (370 . 13) (100 . "AcDbPolyline") (90 . 2) (70 . 0)
(43 . 0.0) (10 13604.8261312217 3495.4751131222) (10 13638.7627828054 3469.0802036199))
((0 . "LWPOLYLINE") (100 . "AcDbEntity") (8 . "PLANTS") (62 . 94) (370 . 13) (100 . "AcDbPolyline") (90 . 2) (70 . 0)
(43 . 0.0) (10 13604.8261312217 3239.0645927602) (10 13615.5387829083 3239.0645927602))
((0 . "LWPOLYLINE") (100 . "AcDbEntity") (8 . "PLANTS") (62 . 94) (370 . 13) (100 . "AcDbPolyline") (90 . 2) (70 . 0)
(43 . 0.0) (10 13604.8261312217 3239.0645927602) (10 13604.8260034445 3235.2941176471))
((0 . "LWPOLYLINE") (100 . "AcDbEntity") (8 . "PLANTS") (62 . 94) (370 . 13) (100 . "AcDbPolyline") (90 . 3) (70 . 0)
(43 . 0.0) (10 13634.9928733032 938.9140271493) (10 13616.1383484163 939.0686651584) (10 13604.8261312217
946.4564479638))
((0 . "LWPOLYLINE") (100 . "AcDbEntity") (8 . "PLANTS") (62 . 94) (370 . 13) (100 . "AcDbPolyline") (90 . 3) (70 . 0)
(43 . 0.0) (10 13604.8261312217 946.4564479638) (10 13608.7450226244 995.3204751131) (10 13612.368438914
999.2449095023))
((0 . "LWPOLYLINE") (100 . "AcDbEntity") (8 . "PLANTS") (62 . 94) (370 . 13) (100 . "AcDbPolyline") (90 . 3) (70 . 0)
(43 . 0.0) (10 13614.2533936652 3955.5048642534) (10 13608.8195701357 3963.0533936652) (10 13608.5972850679
3993.2126696833))
((0 . "LWPOLYLINE") (100 . "AcDbEntity") (8 . "PLANTS") (62 . 94) (370 . 13) (100 . "AcDbPolyline") (90 . 3) (70 . 0)
(43 . 0.0) (10 13608.5972850679 3993.2126696833) (10 13619.0147058824 4023.3719457014) (10 13627.4505656109
4030.9204751131))
((0 . "LWPOLYLINE") (100 . "AcDbEntity") (8 . "PLANTS") (62 . 94) (370 . 13) (100 . "AcDbPolyline") (90 . 3) (70 . 0)
(43 . 0.0) (10 13616.1383484163 3412.5191176471) (10 13606.925 3446.4488687783) (10 13608.5972850679 3453.996719457))
((0 . "LWPOLYLINE") (100 . "AcDbEntity") (8 . "PLANTS") (62 . 94) (370 . 13) (100 . "AcDbPolyline") (90 . 3) (70 . 0)
(43 . 0.0) (10 13612.3679864253 1172.7007918552) (10 13623.6875565611 1166.3563348416) (10 13638.7627828054
1165.1583710407))
((0 . "LWPOLYLINE") (100 . "AcDbEntity") (8 . "PLANTS") (62 . 94) (370 . 13) (100 . "AcDbPolyline") (90 . 2) (70 . 0)
(43 . 0.0) (10 13612.3679864253 1214.1780066683) (10 13612.3679864253 1172.7007918552))
((0 . "LWPOLYLINE") (100 . "AcDbEntity") (8 . "PLANTS") (62 . 94) (370 . 13) (100 . "AcDbPolyline") (90 . 2) (70 . 0)
(43 . 0.0) (10 13612.368438914 3800.9049773756) (10 13623.6806561086 3785.8216063348))
((0 . "LWPOLYLINE") (100 . "AcDbEntity") (8 . "PLANTS") (62 . 94) (370 . 13) (100 . "AcDbPolyline") (90 . 3) (70 . 0)
(43 . 0.0) (10 13627.4505656109 3842.3826923077) (10 13622.624321267 3819.7582579186) (10 13612.368438914
3800.9049773756))
((0 . "LWPOLYLINE") (100 . "AcDbEntity") (8 . "PLANTS") (62 . 94) (370 . 13) (100 . "AcDbPolyline") (90 . 3) (70 . 0)
(43 . 0.0) (10 13612.368438914 3672.6994343891) (10 13619.9164027149 3665.3130090498) (10 13642.5339366516
3665.1583710407))
((0 . "LWPOLYLINE") (100 . "AcDbEntity") (8 . "PLANTS") (62 . 94) (370 . 13) (100 . "AcDbPolyline") (90 . 3) (70 . 0)
(43 . 0.0) (10 13612.368438914 999.2449095023) (10 13642.5339366516 994.2702488688) (10 13653.8461538462
984.1628959276))
((0 . "LWPOLYLINE") (100 . "AcDbEntity") (8 . "PLANTS") (62 . 94) (370 . 13) (100 . "AcDbPolyline") (90 . 3) (70 . 0)
(43 . 0.0) (10 13614.2533936652 3955.5048642534) (10 13623.6130090498 3949.1614253394) (10 13646.3050904977
3944.1926470588))
((0 . "LWPOLYLINE") (100 . "AcDbEntity") (8 . "PLANTS") (62 . 94) (370 . 13) (100 . "AcDbPolyline") (90 . 3) (70 . 0)
(43 . 0.0) (10 13614.2533936652 3955.5048642534) (10 13631.221719457 3969.3837104072) (10 13653.8461538462
3974.3593891403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13665.1583710407 322.3981900452 0.0) (10 13598.687837111 326.3958153735 0.0) (10 13662.2743627521
392.3068899827 0.0) (10 13616.1383484163 407.2398190045 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13616.1383484163 241.3263574661 0.0) (10 13635.6967723337 228.6809915987 0.0) (10 13664.1364250135
230.1079257837 0.0) (10 13680.2417420814 248.8687782805 0.0))
((0 . "LWPOLYLINE") (100 . "AcDbEntity") (8 . "PLANTS") (62 . 94) (370 . 13) (100 . "AcDbPolyline") (90 . 2) (70 . 0)
(43 . 0.0) (10 13616.1383484163 241.3263574661) (10 13619.9095022624 252.6385746606))
((0 . "LWPOLYLINE") (100 . "AcDbEntity") (8 . "PLANTS") (62 . 94) (370 . 13) (100 . "AcDbPolyline") (90 . 2) (70 . 0)
(43 . 0.0) (10 13627.4505656109 4361.0305224188) (10 13627.4505656109 4291.1014705882))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.739639342) (40 .
1) (40 . 1) (40 . 1) (40 . 1) (10 13631.221719457 4079.9392533937 0.0) (10 13630.0282059016 4136.432121644 0.0) (10
13653.7605305016 4202.2460533249 0.0) (10 13646.6265168865 4284.3911163348 0.0) (10 13627.4505656109 4291.1014705883
0.0))
((0 . "LWPOLYLINE") (100 . "AcDbEntity") (8 . "PLANTS") (62 . 94) (370 . 13) (100 . "AcDbPolyline") (90 . 2) (70 . 0)
(43 . 0.0) (10 13627.4505656109 4046.00260181) (10 13627.4505656109 4030.9204751131))
((0 . "LWPOLYLINE") (100 . "AcDbEntity") (8 . "PLANTS") (62 . 94) (370 . 13) (100 . "AcDbPolyline") (90 . 2) (70 . 0)
(43 . 0.0) (10 13627.4505656109 4046.00260181) (10 13631.221719457 4079.9392533937))
((0 . "LWPOLYLINE") (100 . "AcDbEntity") (8 . "PLANTS") (62 . 94) (370 . 13) (100 . "AcDbPolyline") (90 . 2) (70 . 0)
(43 . 0.0) (10 13646.3050904977 4027.149321267) (10 13627.4505656109 4030.9204751131))
((0 . "LWPOLYLINE") (100 . "AcDbEntity") (8 . "PLANTS") (62 . 94) (370 . 13) (100 . "AcDbPolyline") (90 . 2) (70 . 0)
(43 . 0.0) (10 13627.4505656109 3842.3826923077) (10 13631.221719457 3861.2372171946))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13687.7828054299 4110.1059954751 0.0) (10 13673.8839371651 4094.3224938364 0.0) (10 13653.9908368909
4077.4095292173 0.0) (10 13631.221719457 4079.9392533937 0.0))
((0 . "LWPOLYLINE") (100 . "AcDbEntity") (8 . "PLANTS") (62 . 94) (370 . 13) (100 . "AcDbPolyline") (90 . 2) (70 . 0)
(43 . 0.0) (10 13717.9483031674 3872.5494343891) (10 13631.221719457 3861.2372171946))
((0 . "LWPOLYLINE") (100 . "AcDbEntity") (8 . "PLANTS") (62 . 94) (370 . 13) (100 . "AcDbPolyline") (90 . 2) (70 . 0)
(43 . 0.0) (10 13645.001106489 1190.1325497793) (10 13638.7627828054 1165.1583710407))
((0 . "LWPOLYLINE") (100 . "AcDbEntity") (8 . "PLANTS") (62 . 94) (370 . 13) (100 . "AcDbPolyline") (90 . 3) (70 . 0)
(43 . 0.0) (10 13661.3872171946 912.5197963801) (10 13653.8392533937 923.8244343891) (10 13634.9928733032
938.9140271493))
((0 . "LWPOLYLINE") (100 . "AcDbEntity") (8 . "PLANTS") (62 . 94) (370 . 13) (100 . "AcDbPolyline") (90 . 3) (70 . 0)
(43 . 0.0) (10 13634.9928733032 938.9140271493) (10 13643.7311085973 972.850678733) (10 13653.8461538462
984.1628959276))
((0 . "LWPOLYLINE") (100 . "AcDbEntity") (8 . "PLANTS") (62 . 94) (370 . 13) (100 . "AcDbPolyline") (90 . 2) (70 . 0)
(43 . 0.0) (10 13638.7627828054 3906.4860859729) (10 13657.6173076923 3917.7983031674))
((0 . "LWPOLYLINE") (100 . "AcDbEntity") (8 . "PLANTS") (62 . 94) (370 . 13) (100 . "AcDbPolyline") (90 . 2) (70 . 0)
(43 . 0.0) (10 13638.7627828054 3714.1783936652) (10 13650.075 3717.9483031674))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13638.7627828054 1165.1583710407 0.0) (10 13650.502331358 1142.7878370833 0.0) (10 13632.3621957234
1114.7330344298 0.0) (10 13646.3050904977 1093.5152714932 0.0))
((0 . "LWPOLYLINE") (100 . "AcDbEntity") (8 . "PLANTS") (62 . 94) (370 . 13) (100 . "AcDbPolyline") (90 . 3) (70 . 0)
(43 . 0.0) (10 13642.5339366516 3665.1583710407) (10 13646.459841629 3612.367760181) (10 13657.6173076923
3597.2850678733))
((0 . "LWPOLYLINE") (100 . "AcDbEntity") (8 . "PLANTS") (62 . 94) (370 . 13) (100 . "AcDbPolyline") (90 . 2) (70 . 0)
(43 . 0.0) (10 13642.5339366516 3665.1583710407) (10 13650.075 3717.9483031674))
((0 . "LWPOLYLINE") (100 . "AcDbEntity") (8 . "PLANTS") (62 . 94) (370 . 13) (100 . "AcDbPolyline") (90 . 2) (70 . 0)
(43 . 0.0) (10 13702.8661764706 4023.3781674208) (10 13646.3050904977 4027.149321267))
((0 . "LWPOLYLINE") (100 . "AcDbEntity") (8 . "PLANTS") (62 . 94) (370 . 13) (100 . "AcDbPolyline") (90 . 3) (70 . 0)
(43 . 0.0) (10 13653.8461538462 3974.3593891403) (10 13646.4529411765 4000.7537330317) (10 13646.3050904977
4027.149321267))
((0 . "LWPOLYLINE") (100 . "AcDbEntity") (8 . "PLANTS") (62 . 94) (370 . 13) (100 . "AcDbPolyline") (90 . 2) (70 . 0)
(43 . 0.0) (10 13646.3050904977 1093.5152714932) (10 13646.3050904977 1082.2030542986))
((0 . "LWPOLYLINE") (100 . "AcDbEntity") (8 . "PLANTS") (62 . 94) (370 . 13) (100 . "AcDbPolyline") (90 . 3) (70 . 0)
(43 . 0.0) (10 13646.3050904977 1093.5152714932) (10 13657.6173076923 1099.8576923077) (10 13676.4705882353
1102.9411764706))
((0 . "LWPOLYLINE") (100 . "AcDbEntity") (8 . "PLANTS") (62 . 94) (370 . 13) (100 . "AcDbPolyline") (90 . 2) (70 . 0)
(43 . 0.0) (10 13672.6994343891 1078.4304298643) (10 13646.3050904977 1082.2030542986))
((0 . "LWPOLYLINE") (100 . "AcDbEntity") (8 . "PLANTS") (62 . 94) (370 . 13) (100 . "AcDbPolyline") (90 . 2) (70 . 0)
(43 . 0.0) (10 13680.2417420814 263.9507918552) (10 13646.3050904977 279.0356334842))
((0 . "LWPOLYLINE") (100 . "AcDbEntity") (8 . "PLANTS") (62 . 94) (370 . 13) (100 . "AcDbPolyline") (90 . 3) (70 . 0)
(43 . 0.0) (10 13665.1583710407 322.3981900452) (10 13651.2735294118 301.6600678733) (10 13646.3050904977
279.0356334842))
((0 . "LWPOLYLINE") (100 . "AcDbEntity") (8 . "PLANTS") (62 . 94) (370 . 13) (100 . "AcDbPolyline") (90 . 2) (70 . 0)
(43 . 0.0) (10 13672.6994343891 3725.4906108597) (10 13650.075 3725.4906108597))
((0 . "LWPOLYLINE") (100 . "AcDbEntity") (8 . "PLANTS") (62 . 94) (370 . 13) (100 . "AcDbPolyline") (90 . 2) (70 . 0)
(43 . 0.0) (10 13650.075 3725.4906108597) (10 13650.075 3717.9483031674))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3642000227)
(40 . 0.6012011193) (40 . 1) (40 . 1) (40 . 1) (40 . 1) (10 13650.075 3725.4906108597 0.0) (10 13644.8109815362
3742.9518812826 0.0) (10 13655.4310148955 3766.2592249049 0.0) (10 13683.961023699 3798.1062624362 0.0) (10
13685.668852602 3829.0887939599 0.0) (10 13706.6360859729 3831.0704751132 0.0))
((0 . "LWPOLYLINE") (100 . "AcDbEntity") (8 . "PLANTS") (62 . 94) (370 . 13) (100 . "AcDbPolyline") (90 . 3) (70 . 0)
(43 . 0.0) (10 13653.8461538462 3974.3593891403) (10 13680.2417420814 3949.0204751131) (10 13699.0950226244
3944.1926470588))
((0 . "LWPOLYLINE") (100 . "AcDbEntity") (8 . "PLANTS") (62 . 94) (370 . 13) (100 . "AcDbPolyline") (90 . 3) (70 . 0)
(43 . 0.0) (10 13693.4389140272 1057.6923076923) (10 13672.6938914027 1038.1513574661) (10 13653.8461538462
1029.4117647059))
((0 . "LWPOLYLINE") (100 . "AcDbEntity") (8 . "PLANTS") (62 . 94) (370 . 13) (100 . "AcDbPolyline") (90 . 2) (70 . 0)
(43 . 0.0) (10 13680.2417420814 984.1628959276) (10 13653.8461538462 984.1628959276))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13657.6173076923 3597.2850678733 0.0) (10 13664.0980509884 3565.0508151606 0.0) (10 13654.9266936983
3522.2000528053 0.0) (10 13680.2417420814 3495.4751131222 0.0))
((0 . "LWPOLYLINE") (100 . "AcDbEntity") (8 . "PLANTS") (62 . 94) (370 . 13) (100 . "AcDbPolyline") (90 . 3) (70 . 0)
(43 . 0.0) (10 13684.0116515837 3623.6806561086) (10 13680.0871040724 3604.9814479638) (10 13657.6173076923
3597.2850678733))
((0 . "LWPOLYLINE") (100 . "AcDbEntity") (8 . "PLANTS") (62 . 94) (370 . 13) (100 . "AcDbPolyline") (90 . 2) (70 . 0)
(43 . 0.0) (10 13661.3872171946 912.5197963801) (10 13676.4705882353 912.5197963801))
((0 . "LWPOLYLINE") (100 . "AcDbEntity") (8 . "PLANTS") (62 . 94) (370 . 13) (100 . "AcDbPolyline") (90 . 2) (70 . 0)
(43 . 0.0) (10 13665.1583710407 322.3981900452) (10 13680.2417420814 320.5118778281))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7681765522) (40
. 1) (40 . 1) (40 . 1) (40 . 1) (10 13665.1583710407 322.3981900452 0.0) (10 13664.564329393 350.1336886597 0.0) (10
13686.666454583 378.8250531891 0.0) (10 13705.7646491926 405.4935893795 0.0) (10 13710.4072398189 411.0096153847 0.0))
((0 . "LWPOLYLINE") (100 . "AcDbEntity") (8 . "PLANTS") (62 . 94) (370 . 13) (100 . "AcDbPolyline") (90 . 2) (70 . 0)
(43 . 0.0) (10 13699.0950226244 505.2799773756) (10 13668.9295248869 520.3619909502))
((0 . "LWPOLYLINE") (100 . "AcDbEntity") (8 . "PLANTS") (62 . 94) (370 . 13) (100 . "AcDbPolyline") (90 . 2) (70 . 0)
(43 . 0.0) (10 13672.6994343891 3725.4906108597) (10 13717.9483031674 3725.4906108597))
((0 . "LWPOLYLINE") (100 . "AcDbEntity") (8 . "PLANTS") (62 . 94) (370 . 13) (100 . "AcDbPolyline") (90 . 2) (70 . 0)
(43 . 0.0) (10 13672.6994343891 3725.4906108597) (10 13680.2417420814 3702.8661764706))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4020516812)
(40 . 0.5636576626) (40 . 1) (40 . 1) (40 . 1) (40 . 1) (10 13672.6994343891 3725.4906108597 0.0) (10 13671.4487017718
3750.5824195102 0.0) (10 13701.1048452742 3760.2584634042 0.0) (10 13718.5556557161 3805.5048210113 0.0) (10
13756.0343943003 3805.1836211349 0.0) (10 13774.5093891403 3808.446040724 0.0))
((0 . "LWPOLYLINE") (100 . "AcDbEntity") (8 . "PLANTS") (62 . 94) (370 . 13) (100 . "AcDbPolyline") (90 . 2) (70 . 0)
(43 . 0.0) (10 13693.4389140272 1057.6923076923) (10 13672.6994343891 1078.4304298643))
((0 . "LWPOLYLINE") (100 . "AcDbEntity") (8 . "PLANTS") (62 . 94) (370 . 13) (100 . "AcDbPolyline") (90 . 2) (70 . 0)
(43 . 0.0) (10 13672.6994343891 1078.4304298643) (10 13676.4705882353 1102.9411764706))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13676.4705882353 1102.9411764706 0.0) (10 13667.0570967513 1124.2859865522 0.0) (10 13687.8384730588
1143.3523997943 0.0) (10 13706.6360859729 1138.7641402715 0.0))
((0 . "LWPOLYLINE") (100 . "AcDbEntity") (8 . "PLANTS") (62 . 94) (370 . 13) (100 . "AcDbPolyline") (90 . 3) (70 . 0)
(43 . 0.0) (10 13710.407239819 1119.9095022624) (10 13695.1760180995 1106.0308823529) (10 13676.4705882353
1102.9411764706))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13785.8216063349 904.9773755656 0.0) (10 13750.4515820137 894.5960119505 0.0) (10 13708.8324544082
889.590920133 0.0) (10 13676.4705882353 912.5197963801 0.0))
((0 . "LWPOLYLINE") (100 . "AcDbEntity") (8 . "PLANTS") (62 . 94) (370 . 13) (100 . "AcDbPolyline") (90 . 3) (70 . 0)
(43 . 0.0) (10 13680.2417420814 984.1628959276) (10 13680.0940045249 923.8320135747) (10 13676.4705882353
912.5197963801))
((0 . "LWPOLYLINE") (100 . "AcDbEntity") (8 . "PLANTS") (62 . 94) (370 . 13) (100 . "AcDbPolyline") (90 . 2) (70 . 0)
(43 . 0.0) (10 13687.7828054299 984.1628959276) (10 13680.2417420814 984.1628959276))
((0 . "LWPOLYLINE") (100 . "AcDbEntity") (8 . "PLANTS") (62 . 94) (370 . 13) (100 . "AcDbPolyline") (90 . 2) (70 . 0)
(43 . 0.0) (10 13680.2417420814 305.4298642534) (10 13680.2417420814 320.5118778281))
((0 . "LWPOLYLINE") (100 . "AcDbEntity") (8 . "PLANTS") (62 . 94) (370 . 13) (100 . "AcDbPolyline") (90 . 3) (70 . 0)
(43 . 0.0) (10 13782.0516968326 380.8455882353) (10 13717.9483031674 349.62239819) (10 13680.2417420814 320.5118778281))
((0 . "LWPOLYLINE") (100 . "AcDbEntity") (8 . "PLANTS") (62 . 94) (370 . 13) (100 . "AcDbPolyline") (90 . 2) (70 . 0)
(43 . 0.0) (10 13680.2417420814 305.4298642534) (10 13684.0116515837 297.8874434389))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13680.2417420814 305.4298642534 0.0) (10 13671.6924676905 309.7788622439 0.0) (10 13677.9936251104
292.1353289019 0.0) (10 13684.0116515837 297.8874434389 0.0))
((0 . "LWPOLYLINE") (100 . "AcDbEntity") (8 . "PLANTS") (62 . 94) (370 . 13) (100 . "AcDbPolyline") (90 . 2) (70 . 0)
(43 . 0.0) (10 13680.2417420814 263.9507918552) (10 13680.2417420814 248.8687782805))
((0 . "LWPOLYLINE") (100 . "AcDbEntity") (8 . "PLANTS") (62 . 94) (370 . 13) (100 . "AcDbPolyline") (90 . 3) (70 . 0)
(43 . 0.0) (10 13680.2417420814 263.9507918552) (10 13686.5856334842 271.5001131222) (10 13691.553959276
290.3478506787))
((0 . "LWPOLYLINE") (100 . "AcDbEntity") (8 . "PLANTS") (62 . 94) (370 . 13) (100 . "AcDbPolyline") (90 . 3) (70 . 0)
(43 . 0.0) (10 13680.2417420814 248.8687782805) (10 13699.0950226244 237.7049773756) (10 13736.8028280543
241.3263574661))
((0 . "LWPOLYLINE") (100 . "AcDbEntity") (8 . "PLANTS") (62 . 94) (370 . 13) (100 . "AcDbPolyline") (90 . 3) (70 . 0)
(43 . 0.0) (10 13684.0116515837 3684.0116515837) (10 13696.3802036199 3650.075678733) (10 13710.407239819
3638.7627828054))
((0 . "LWPOLYLINE") (100 . "AcDbEntity") (8 . "PLANTS") (62 . 94) (370 . 13) (100 . "AcDbPolyline") (90 . 2) (70 . 0)
(43 . 0.0) (10 13684.0116515837 297.8874434389) (10 13691.553959276 290.3478506787))
((0 . "LWPOLYLINE") (100 . "AcDbEntity") (8 . "PLANTS") (62 . 94) (370 . 13) (100 . "AcDbPolyline") (90 . 3) (70 . 0)
(43 . 0.0) (10 13719.8345022624 4096.9075791855) (10 13695.3307692308 4103.7615384615) (10 13687.7828054299
4110.1059954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13687.7828054299 4110.1059954751 0.0) (10 13685.331860545 4122.1776318947 0.0) (10 13687.4993871468
4144.050482687 0.0) (10 13702.8661764706 4147.8125565611 0.0))
((0 . "LWPOLYLINE") (100 . "AcDbEntity") (8 . "PLANTS") (62 . 94) (370 . 13) (100 . "AcDbPolyline") (90 . 2) (70 . 0)
(43 . 0.0) (10 13687.7828054299 984.1628959276) (10 13774.5093891403 961.5384615385))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13702.8661764706 1033.181561086 0.0) (10 13684.3211508899 1026.7958101458 0.0) (10 13689.2550787182
997.5089559926 0.0) (10 13687.7828054299 984.1628959276 0.0))
((0 . "LWPOLYLINE") (100 . "AcDbEntity") (8 . "PLANTS") (62 . 94) (370 . 13) (100 . "AcDbPolyline") (90 . 2) (70 . 0)
(43 . 0.0) (10 13691.553959276 290.3478506787) (10 13706.6360859729 290.3478506787))
((0 . "LWPOLYLINE") (100 . "AcDbEntity") (8 . "PLANTS") (62 . 94) (370 . 13) (100 . "AcDbPolyline") (90 . 3) (70 . 0)
(43 . 0.0) (10 13702.8661764706 1033.181561086) (10 13701.5944570136 1048.3333710407) (10 13693.4389140272
1057.6923076923))
((0 . "LWPOLYLINE") (100 . "AcDbEntity") (8 . "PLANTS") (62 . 94) (370 . 13) (100 . "AcDbPolyline") (90 . 3) (70 . 0)
(43 . 0.0) (10 13693.4389140272 1057.6923076923) (10 13714.1783936652 1073.4626696833) (10 13729.260520362
1074.6606334842))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13725.4906108597 3887.631561086 0.0) (10 13729.4215930067 3911.3832916093 0.0) (10 13695.4425315586
3919.4077390362 0.0) (10 13699.0950226244 3944.1926470588 0.0))
((0 . "LWPOLYLINE") (100 . "AcDbEntity") (8 . "PLANTS") (62 . 94) (370 . 13) (100 . "AcDbPolyline") (90 . 2) (70 . 0)
(43 . 0.0) (10 13699.0950226244 3944.1926470588) (10 13706.6360859729 3947.963800905))
((0 . "LWPOLYLINE") (100 . "AcDbEntity") (8 . "PLANTS") (62 . 94) (370 . 13) (100 . "AcDbPolyline") (90 . 2) (70 . 0)
(43 . 0.0) (10 13699.0950226244 505.2799773756) (10 13702.8661764706 497.7375565611))
((0 . "LWPOLYLINE") (100 . "AcDbEntity") (8 . "PLANTS") (62 . 94) (370 . 13) (100 . "AcDbPolyline") (90 . 2) (70 . 0)
(43 . 0.0) (10 13706.6360859729 531.6742081448) (10 13699.0950226244 505.2799773756))
((0 . "LWPOLYLINE") (100 . "AcDbEntity") (8 . "PLANTS") (62 . 94) (370 . 13) (100 . "AcDbPolyline") (90 . 2) (70 . 0)
(43 . 0.0) (10 13702.8661764706 4147.8125565611) (10 13702.9470326239 4193.1796636174))
((0 . "LWPOLYLINE") (100 . "AcDbEntity") (8 . "PLANTS") (62 . 94) (370 . 13) (100 . "AcDbPolyline") (90 . 3) (70 . 0)
(43 . 0.0) (10 13719.8345022624 4096.9075791855) (10 13720.5152714932 4132.7235294118) (10 13702.8661764706
4147.8125565611))
((0 . "LWPOLYLINE") (100 . "AcDbEntity") (8 . "PLANTS") (62 . 94) (370 . 13) (100 . "AcDbPolyline") (90 . 3) (70 . 0)
(43 . 0.0) (10 13710.407239819 3981.9004524887) (10 13710.2595022624 4000.7537330317) (10 13702.8661764706
4023.3781674208))
((0 . "LWPOLYLINE") (100 . "AcDbEntity") (8 . "PLANTS") (62 . 94) (370 . 13) (100 . "AcDbPolyline") (90 . 3) (70 . 0)
(43 . 0.0) (10 13706.6360859729 4030.9204751131) (10 13702.8661764706 4030.9204751131) (10 13702.8661764706
4023.3781674208))
((0 . "LWPOLYLINE") (100 . "AcDbEntity") (8 . "PLANTS") (62 . 94) (370 . 13) (100 . "AcDbPolyline") (90 . 2) (70 . 0)
(43 . 0.0) (10 13706.6360859729 4030.9204751131) (10 13702.8661764706 4023.3781674208))
((0 . "LWPOLYLINE") (100 . "AcDbEntity") (8 . "PLANTS") (62 . 94) (370 . 13) (100 . "AcDbPolyline") (90 . 2) (70 . 0)
(43 . 0.0) (10 13702.8661764706 1033.181561086) (10 13770.739479638 1006.7873303167))
((0 . "LWPOLYLINE") (100 . "AcDbEntity") (8 . "PLANTS") (62 . 94) (370 . 13) (100 . "AcDbPolyline") (90 . 3) (70 . 0)
(43 . 0.0) (10 13706.6360859729 4030.9204751131) (10 13736.8028280543 4023.5265837104) (10 13778.2805429864
4023.3781674208))
((0 . "LWPOLYLINE") (100 . "AcDbEntity") (8 . "PLANTS") (62 . 94) (370 . 13) (100 . "AcDbPolyline") (90 . 3) (70 . 0)
(43 . 0.0) (10 13706.6360859729 4030.9204751131) (10 13717.8004524887 4072.3981900452) (10 13719.8345022624
4096.9075791855))
((0 . "LWPOLYLINE") (100 . "AcDbEntity") (8 . "PLANTS") (62 . 94) (370 . 13) (100 . "AcDbPolyline") (90 . 2) (70 . 0)
(43 . 0.0) (10 13725.4906108597 3947.963800905) (10 13706.6360859729 3947.963800905))
((0 . "LWPOLYLINE") (100 . "AcDbEntity") (8 . "PLANTS") (62 . 94) (370 . 13) (100 . "AcDbPolyline") (90 . 3) (70 . 0)
(43 . 0.0) (10 13710.407239819 3981.9004524887) (10 13706.7838235294 3974.3524886878) (10 13706.6360859729
3947.963800905))
((0 . "LWPOLYLINE") (100 . "AcDbEntity") (8 . "PLANTS") (62 . 94) (370 . 13) (100 . "AcDbPolyline") (90 . 2) (70 . 0)
(43 . 0.0) (10 13710.407239819 1119.9095022624) (10 13706.6360859729 1138.7641402715))
((0 . "LWPOLYLINE") (100 . "AcDbEntity") (8 . "PLANTS") (62 . 94) (370 . 13) (100 . "AcDbPolyline") (90 . 2) (70 . 0)
(43 . 0.0) (10 13710.1720844658 1142.1118291647) (10 13706.6360859729 1138.7641402715))
((0 . "LWPOLYLINE") (100 . "AcDbEntity") (8 . "PLANTS") (62 . 94) (370 . 13) (100 . "AcDbPolyline") (90 . 3) (70 . 0)
(43 . 0.0) (10 13706.6360859729 290.3478506787) (10 13724.4342760181 271.4869909502) (10 13736.8028280543
241.3263574661))
((0 . "LWPOLYLINE") (100 . "AcDbEntity") (8 . "PLANTS") (62 . 94) (370 . 13) (100 . "AcDbPolyline") (90 . 3) (70 . 0)
(43 . 0.0) (10 13744.3438914027 324.2845022624) (10 13740.4179864253 316.882918552) (10 13706.6360859729
290.3478506787))
((0 . "LWPOLYLINE") (100 . "AcDbEntity") (8 . "PLANTS") (62 . 94) (370 . 13) (100 . "AcDbPolyline") (90 . 3) (70 . 0)
(43 . 0.0) (10 13710.407239819 3981.9004524887) (10 13729.1057692308 3976.9385746606) (10 13733.0316742081
3970.5882352941))
((0 . "LWPOLYLINE") (100 . "AcDbEntity") (8 . "PLANTS") (62 . 94) (370 . 13) (100 . "AcDbPolyline") (90 . 3) (70 . 0)
(43 . 0.0) (10 13729.260520362 1074.6606334842) (10 13728.2040723982 1101.0548642534) (10 13710.407239819
1119.9095022624))
((0 . "LWPOLYLINE") (100 . "AcDbEntity") (8 . "PLANTS") (62 . 94) (370 . 13) (100 . "AcDbPolyline") (90 . 3) (70 . 0)
(43 . 0.0) (10 13710.407239819 411.0096153846) (10 13729.2536199095 402.7160633484) (10 13736.8028280543
403.4700226244))
((0 . "LWPOLYLINE") (100 . "AcDbEntity") (8 . "PLANTS") (62 . 94) (370 . 13) (100 . "AcDbPolyline") (90 . 2) (70 . 0)
(43 . 0.0) (10 13710.407239819 411.0096153846) (10 13714.1783936652 422.3218325792))
((0 . "LWPOLYLINE") (100 . "AcDbEntity") (8 . "PLANTS") (62 . 94) (370 . 13) (100 . "AcDbPolyline") (90 . 3) (70 . 0)
(43 . 0.0) (10 13717.9483031674 3872.5494343891) (10 13725.4975113122 3861.2430995475) (10 13740.5727375566 3849.925))
((0 . "LWPOLYLINE") (100 . "AcDbEntity") (8 . "PLANTS") (62 . 94) (370 . 13) (100 . "AcDbPolyline") (90 . 2) (70 . 0)
(43 . 0.0) (10 13717.9483031674 3872.5494343891) (10 13725.4906108597 3887.631561086))
((0 . "LWPOLYLINE") (100 . "AcDbEntity") (8 . "PLANTS") (62 . 94) (370 . 13) (100 . "AcDbPolyline") (90 . 2) (70 . 0)
(43 . 0.0) (10 13720.6636424445 3721.4177139487) (10 13717.9483031674 3725.4906108597))
((0 . "LWPOLYLINE") (100 . "AcDbEntity") (8 . "PLANTS") (62 . 94) (370 . 13) (100 . "AcDbPolyline") (90 . 2) (70 . 0)
(43 . 0.0) (10 13717.9483031674 3725.4906108597) (10 13721.3695210544 3729.1823786572))
((0 . "LWPOLYLINE") (100 . "AcDbEntity") (8 . "PLANTS") (62 . 94) (370 . 13) (100 . "AcDbPolyline") (90 . 3) (70 . 0)
(43 . 0.0) (10 13724.9367223286 3733.0316742081) (10 13729.260520362 3737.69739819) (10 13755.6561085973
3744.3438914027))
((0 . "LWPOLYLINE") (100 . "AcDbEntity") (8 . "PLANTS") (62 . 94) (370 . 13) (100 . "AcDbPolyline") (90 . 3) (70 . 0)
(43 . 0.0) (10 13717.9483031674 471.3433257919) (10 13777.2242081448 399.69739819) (10 13782.0516968326 380.8455882353))
((0 . "LWPOLYLINE") (100 . "AcDbEntity") (8 . "PLANTS") (62 . 94) (370 . 13) (100 . "AcDbPolyline") (90 . 2) (70 . 0)
(43 . 0.0) (10 13719.8345022624 4096.9075791855) (10 13741.3478643556 4100.3776535991))
((0 . "LWPOLYLINE") (100 . "AcDbEntity") (8 . "PLANTS") (62 . 94) (370 . 13) (100 . "AcDbPolyline") (90 . 3) (70 . 0)
(43 . 0.0) (10 13800.9049773756 3857.4660633484) (10 13785.8216063348 3871.3446832579) (10 13725.4906108597
3887.631561086))
((0 . "LWPOLYLINE") (100 . "AcDbEntity") (8 . "PLANTS") (62 . 94) (370 . 13) (100 . "AcDbPolyline") (90 . 2) (70 . 0)
(43 . 0.0) (10 13729.260520362 1074.6606334842) (10 13766.9683257919 1074.6606334842))
((0 . "LWPOLYLINE") (100 . "AcDbEntity") (8 . "PLANTS") (62 . 94) (370 . 13) (100 . "AcDbPolyline") (90 . 3) (70 . 0)
(43 . 0.0) (10 13804.6761312217 237.556561086) (10 13778.2805429864 230.1625565611) (10 13736.8028280543
241.3263574661))
((0 . "LWPOLYLINE") (100 . "AcDbEntity") (8 . "PLANTS") (62 . 94) (370 . 13) (100 . "AcDbPolyline") (90 . 3) (70 . 0)
(43 . 0.0) (10 13778.2805429864 3959.2760180995) (10 13759.4272624434 3947.8157239819) (10 13748.1150452489
3932.8804298643))
((0 . "LWPOLYLINE") (100 . "AcDbEntity") (8 . "PLANTS") (62 . 94) (370 . 13) (100 . "AcDbPolyline") (90 . 2) (70 . 0)
(43 . 0.0) (10 13768.583975904 3733.0316742081) (10 13755.6561085973 3744.3438914027))
((0 . "LWPOLYLINE") (100 . "AcDbEntity") (8 . "PLANTS") (62 . 94) (370 . 13) (100 . "AcDbPolyline") (90 . 3) (70 . 0)
(43 . 0.0) (10 13774.5093891403 3793.3639140271) (10 13760.4837104072 3770.739479638) (10 13755.6561085973
3744.3438914027))
((0 . "LWPOLYLINE") (100 . "AcDbEntity") (8 . "PLANTS") (62 . 94) (370 . 13) (100 . "AcDbPolyline") (90 . 3) (70 . 0)
(43 . 0.0) (10 13755.6561085973 294.1176470588) (10 13752.1817873303 286.5703619909) (10 13759.4272624434
271.4932126697))
((0 . "LWPOLYLINE") (100 . "AcDbEntity") (8 . "PLANTS") (62 . 94) (370 . 13) (100 . "AcDbPolyline") (90 . 2) (70 . 0)
(43 . 0.0) (10 13766.9683257919 1112.0401337793) (10 13766.9683257919 1074.6606334842))
((0 . "LWPOLYLINE") (100 . "AcDbEntity") (8 . "PLANTS") (62 . 94) (370 . 13) (100 . "AcDbPolyline") (90 . 2) (70 . 0)
(43 . 0.0) (10 13770.739479638 1067.1182126697) (10 13766.9683257919 1074.6606334842))
((0 . "LWPOLYLINE") (100 . "AcDbEntity") (8 . "PLANTS") (62 . 94) (370 . 13) (100 . "AcDbPolyline") (90 . 3) (70 . 0)
(43 . 0.0) (10 13770.739479638 1006.7873303167) (10 13774.5093891403 1029.4117647059) (10 13770.739479638
1067.1182126697))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6281065568) (40
. 1) (40 . 1) (40 . 1) (40 . 1) (10 13823.5294117647 999.2449095023 0.0) (10 13806.587056144 1014.4422521352 0.0) (10
13823.5190151391 1065.8749431594 0.0) (10 13788.789423359 1076.8118830856 0.0) (10 13770.739479638 1067.1182126697 0.0))
((0 . "LWPOLYLINE") (100 . "AcDbEntity") (8 . "PLANTS") (62 . 94) (370 . 13) (100 . "AcDbPolyline") (90 . 2) (70 . 0)
(43 . 0.0) (10 13770.739479638 1006.7873303167) (10 13774.5093891403 1003.0175339367))
((0 . "LWPOLYLINE") (100 . "AcDbEntity") (8 . "PLANTS") (62 . 94) (370 . 13) (100 . "AcDbPolyline") (90 . 3) (70 . 0)
(43 . 0.0) (10 13770.739479638 1006.7873303167) (10 13770.739479638 1003.0175339367) (10 13774.5093891403
1003.0175339367))
((0 . "LWPOLYLINE") (100 . "AcDbEntity") (8 . "PLANTS") (62 . 94) (370 . 13) (100 . "AcDbPolyline") (90 . 2) (70 . 0)
(43 . 0.0) (10 13774.5093891403 3793.3639140271) (10 13774.5093891403 3808.446040724))
((0 . "LWPOLYLINE") (100 . "AcDbEntity") (8 . "PLANTS") (62 . 94) (370 . 13) (100 . "AcDbPolyline") (90 . 3) (70 . 0)
(43 . 0.0) (10 13800.9049773756 3838.6127828054) (10 13778.4351809955 3819.7589366516) (10 13774.5093891403
3808.446040724))
((0 . "LWPOLYLINE") (100 . "AcDbEntity") (8 . "PLANTS") (62 . 94) (370 . 13) (100 . "AcDbPolyline") (90 . 3) (70 . 0)
(43 . 0.0) (10 13774.5093891403 3793.3639140271) (10 13815.9883484163 3778.4286199095) (10 13838.6127828054
3778.2805429864))
((0 . "LWPOLYLINE") (100 . "AcDbEntity") (8 . "PLANTS") (62 . 94) (370 . 13) (100 . "AcDbPolyline") (90 . 2) (70 . 0)
(43 . 0.0) (10 13774.5093891403 961.5384615385) (10 13774.5093891403 1003.0175339367))
((0 . "LWPOLYLINE") (100 . "AcDbEntity") (8 . "PLANTS") (62 . 94) (370 . 13) (100 . "AcDbPolyline") (90 . 2) (70 . 0)
(43 . 0.0) (10 13785.8216063348 1006.7873303167) (10 13774.5093891403 1003.0175339367))
((0 . "LWPOLYLINE") (100 . "AcDbEntity") (8 . "PLANTS") (62 . 94) (370 . 13) (100 . "AcDbPolyline") (90 . 2) (70 . 0)
(43 . 0.0) (10 13785.8216063348 935.1442307692) (10 13774.5093891403 961.5384615385))
((0 . "LWPOLYLINE") (100 . "AcDbEntity") (8 . "PLANTS") (62 . 94) (370 . 13) (100 . "AcDbPolyline") (90 . 2) (70 . 0)
(43 . 0.0) (10 13785.2853587589 4042.2326923077) (10 13812.2171945701 4042.2326923077))
((0 . "LWPOLYLINE") (100 . "AcDbEntity") (8 . "PLANTS") (62 . 94) (370 . 13) (100 . "AcDbPolyline") (90 . 2) (70 . 0)
(43 . 0.0) (10 13778.2805429864 4040.7905243545) (10 13778.2805429864 4023.3781674208))
((0 . "LWPOLYLINE") (100 . "AcDbEntity") (8 . "PLANTS") (62 . 94) (370 . 13) (100 . "AcDbPolyline") (90 . 3) (70 . 0)
(43 . 0.0) (10 13778.2805429864 3959.2760180995) (10 13774.8048642534 3970.5882352941) (10 13778.2805429864
4023.3781674208))
((0 . "LWPOLYLINE") (100 . "AcDbEntity") (8 . "PLANTS") (62 . 94) (370 . 13) (100 . "AcDbPolyline") (90 . 3) (70 . 0)
(43 . 0.0) (10 13778.2805429864 3959.2760180995) (10 13789.74739819 3936.6578054299) (10 13804.6761312217
3925.3393665158))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13815.9883484163 350.6787330317 0.0) (10 13799.2627642301 354.2794626846 0.0) (10 13800.418954508
382.6120422322 0.0) (10 13782.0516968326 380.8455882353 0.0))
((0 . "LWPOLYLINE") (100 . "AcDbEntity") (8 . "PLANTS") (62 . 94) (370 . 13) (100 . "AcDbPolyline") (90 . 3) (70 . 0)
(43 . 0.0) (10 13785.8216063348 935.1442307692) (10 13815.9883484163 933.9393665158) (10 13834.8416289593
916.2895927602))
((0 . "LWPOLYLINE") (100 . "AcDbEntity") (8 . "PLANTS") (62 . 94) (370 . 13) (100 . "AcDbPolyline") (90 . 2) (70 . 0)
(43 . 0.0) (10 13785.8216063348 935.1442307692) (10 13785.8216063348 904.9773755656))
((0 . "LWPOLYLINE") (100 . "AcDbEntity") (8 . "PLANTS") (62 . 94) (370 . 13) (100 . "AcDbPolyline") (90 . 3) (70 . 0)
(43 . 0.0) (10 13785.8216063348 904.9773755656) (10 13819.7582579186 905.1320135747) (10 13834.8416289593
916.2895927602))
((0 . "LWPOLYLINE") (100 . "AcDbEntity") (8 . "PLANTS") (62 . 94) (370 . 13) (100 . "AcDbPolyline") (90 . 2) (70 . 0)
(43 . 0.0) (10 13800.9049773756 3857.4660633484) (10 13800.9049773756 3838.6127828054))
((0 . "LWPOLYLINE") (100 . "AcDbEntity") (8 . "PLANTS") (62 . 94) (370 . 13) (100 . "AcDbPolyline") (90 . 3) (70 . 0)
(43 . 0.0) (10 13800.9049773756 3857.4660633484) (10 13808.446040724 3865.0071266968) (10 13808.446040724
3872.5494343891))
((0 . "LWPOLYLINE") (100 . "AcDbEntity") (8 . "PLANTS") (62 . 94) (370 . 13) (100 . "AcDbPolyline") (90 . 2) (70 . 0)
(43 . 0.0) (10 13842.3826923077 3812.2171945701) (10 13800.9049773756 3838.6127828054))
((0 . "LWPOLYLINE") (100 . "AcDbEntity") (8 . "PLANTS") (62 . 94) (370 . 13) (100 . "AcDbPolyline") (90 . 3) (70 . 0)
(43 . 0.0) (10 13863.1221719457 3904.5998868778) (10 13838.6127828054 3920.5190045249) (10 13804.6761312217
3925.3393665158))
((0 . "LWPOLYLINE") (100 . "AcDbEntity") (8 . "PLANTS") (62 . 94) (370 . 13) (100 . "AcDbPolyline") (90 . 2) (70 . 0)
(43 . 0.0) (10 13808.446040724 3872.5494343891) (10 13804.6761312217 3925.3393665158))
((0 . "LWPOLYLINE") (100 . "AcDbEntity") (8 . "PLANTS") (62 . 94) (370 . 13) (100 . "AcDbPolyline") (90 . 2) (70 . 0)
(43 . 0.0) (10 13836.5157786324 513.0656352229) (10 13804.6761312217 516.5921945701))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13891.4027149321 248.8687782805 0.0) (10 13873.1859104173 214.668241718 0.0) (10 13831.8284304423
232.8577217503 0.0) (10 13804.6761312217 237.556561086 0.0))
((0 . "LWPOLYLINE") (100 . "AcDbEntity") (8 . "PLANTS") (62 . 94) (370 . 13) (100 . "AcDbPolyline") (90 . 2) (70 . 0)
(43 . 0.0) (10 13804.6761312217 237.556561086) (10 13815.9883484163 350.6787330317))
((0 . "LWPOLYLINE") (100 . "AcDbEntity") (8 . "PLANTS") (62 . 94) (370 . 13) (100 . "AcDbPolyline") (90 . 3) (70 . 0)
(43 . 0.0) (10 13863.1221719457 3904.5998868778) (10 13846.1469457014 3881.2881221719) (10 13808.446040724
3872.5494343891))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13812.2171945701 4042.2326923077 0.0) (10 13819.1524320985 4027.686711984 0.0) (10 13833.7432153333
4005.4891598544 0.0) (10 13853.6949095023 4008.296040724 0.0))
((0 . "LWPOLYLINE") (100 . "AcDbEntity") (8 . "PLANTS") (62 . 94) (370 . 13) (100 . "AcDbPolyline") (90 . 2) (70 . 0)
(43 . 0.0) (10 13812.2171945701 4042.2326923077) (10 13816.5019413854 4048.6596357896))
((0 . "LWPOLYLINE") (100 . "AcDbEntity") (8 . "PLANTS") (62 . 94) (370 . 13) (100 . "AcDbPolyline") (90 . 3) (70 . 0)
(43 . 0.0) (10 13815.9883484163 972.850678733) (10 13817.0447963801 987.9326923077) (10 13823.5294117647
999.2449095023))
((0 . "LWPOLYLINE") (100 . "AcDbEntity") (8 . "PLANTS") (62 . 94) (370 . 13) (100 . "AcDbPolyline") (90 . 3) (70 . 0)
(43 . 0.0) (10 13853.6949095023 395.92760181) (10 13838.4581447964 365.7607466063) (10 13815.9883484163 350.6787330317))
((0 . "LWPOLYLINE") (100 . "AcDbEntity") (8 . "PLANTS") (62 . 94) (370 . 13) (100 . "AcDbPolyline") (90 . 2) (70 . 0)
(43 . 0.0) (10 13823.5294117647 999.2449095023) (10 13842.3826923077 999.2449095023))
((0 . "LWPOLYLINE") (100 . "AcDbEntity") (8 . "PLANTS") (62 . 94) (370 . 13) (100 . "AcDbPolyline") (90 . 2) (70 . 0)
(43 . 0.0) (10 13846.1538461538 916.2895927602) (10 13834.8416289593 916.2895927602))
((0 . "LWPOLYLINE") (100 . "AcDbEntity") (8 . "PLANTS") (62 . 94) (370 . 13) (100 . "AcDbPolyline") (90 . 2) (70 . 0)
(43 . 0.0) (10 13838.6127828054 3778.2805429864) (10 13853.6949095023 3748.1150452489))
((0 . "LWPOLYLINE") (100 . "AcDbEntity") (8 . "PLANTS") (62 . 94) (370 . 13) (100 . "AcDbPolyline") (90 . 3) (70 . 0)
(43 . 0.0) (10 13842.3826923077 3812.2171945701) (10 13838.7606334842 3804.6692307692) (10 13838.6127828054
3778.2805429864))
((0 . "LWPOLYLINE") (100 . "AcDbEntity") (8 . "PLANTS") (62 . 94) (370 . 13) (100 . "AcDbPolyline") (90 . 2) (70 . 0)
(43 . 0.0) (10 13838.6127828054 452.4886877828) (10 13853.6949095023 395.92760181))
((0 . "LWPOLYLINE") (100 . "AcDbEntity") (8 . "PLANTS") (62 . 94) (370 . 13) (100 . "AcDbPolyline") (90 . 2) (70 . 0)
(43 . 0.0) (10 13842.3826923077 3812.2171945701) (10 13857.4660633484 3812.2171945701))
((0 . "LWPOLYLINE") (100 . "AcDbEntity") (8 . "PLANTS") (62 . 94) (370 . 13) (100 . "AcDbPolyline") (90 . 2) (70 . 0)
(43 . 0.0) (10 13846.1532239819 3733.0316742081) (10 13853.6949095023 3748.1150452489))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13842.3826923077 999.2449095023 0.0) (10 13858.0775864564 977.3682929044 0.0) (10 13824.9423673506
943.0508085202 0.0) (10 13849.925 927.6018099548 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13857.4660633484 1036.9541855204 0.0) (10 13844.1762489795 1027.2030804178 0.0) (10 13856.7213993811
1007.7275044571 0.0) (10 13842.3826923077 999.2449095023 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13974.3593891403 901.2075791855 0.0) (10 13948.3890510001 918.2726252419 0.0) (10 13872.2313025097
873.8821355362 0.0) (10 13846.1538461538 916.2895927602 0.0))
((0 . "LWPOLYLINE") (100 . "AcDbEntity") (8 . "PLANTS") (62 . 94) (370 . 13) (100 . "AcDbPolyline") (90 . 2) (70 . 0)
(43 . 0.0) (10 13846.1538461538 916.2895927602) (10 13849.925 927.6018099548))
((0 . "LWPOLYLINE") (100 . "AcDbEntity") (8 . "PLANTS") (62 . 94) (370 . 13) (100 . "AcDbPolyline") (90 . 2) (70 . 0)
(43 . 0.0) (10 13883.8616515837 950.2262443439) (10 13849.925 927.6018099548))
((0 . "LWPOLYLINE") (100 . "AcDbEntity") (8 . "PLANTS") (62 . 94) (370 . 13) (100 . "AcDbPolyline") (90 . 3) (70 . 0)
(43 . 0.0) (10 13863.1221719457 3904.5998868778) (10 13864.8592760181 3959.2760180995) (10 13853.6949095023
4008.296040724))
((0 . "LWPOLYLINE") (100 . "AcDbEntity") (8 . "PLANTS") (62 . 94) (370 . 13) (100 . "AcDbPolyline") (90 . 3) (70 . 0)
(43 . 0.0) (10 13853.6949095023 4008.296040724) (10 13861.2367647059 4023.3781674208) (10 13861.2367647059
4057.8697464732))
((0 . "LWPOLYLINE") (100 . "AcDbEntity") (8 . "PLANTS") (62 . 94) (370 . 13) (100 . "AcDbPolyline") (90 . 2) (70 . 0)
(43 . 0.0) (10 13876.3193438914 3751.8849547511) (10 13853.6949095023 3748.1150452489))
((0 . "LWPOLYLINE") (100 . "AcDbEntity") (8 . "PLANTS") (62 . 94) (370 . 13) (100 . "AcDbPolyline") (90 . 3) (70 . 0)
(43 . 0.0) (10 13846.2529587235 1136.1702394541) (10 13846.3084841629 1055.8135746606) (10 13857.4660633484
1044.4937782805))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13898.9437782805 422.3218325792 0.0) (10 13890.1226394127 406.9103205896 0.0) (10 13873.5742304659
390.7150833289 0.0) (10 13853.6949095023 395.92760181 0.0))
((0 . "LWPOLYLINE") (100 . "AcDbEntity") (8 . "PLANTS") (62 . 94) (370 . 13) (100 . "AcDbPolyline") (90 . 3) (70 . 0)
(43 . 0.0) (10 13857.4660633484 3812.2171945701) (10 13868.778280543 3805.731561086) (10 13898.9437782805
3800.9049773756))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13857.4660633484 3812.2171945701 0.0) (10 13859.5821102027 3847.2238625192 0.0) (10 13907.3897304908
3844.6128198359 0.0) (10 13906.4860859729 3880.0904977376 0.0))
((0 . "LWPOLYLINE") (100 . "AcDbEntity") (8 . "PLANTS") (62 . 94) (370 . 13) (100 . "AcDbPolyline") (90 . 2) (70 . 0)
(43 . 0.0) (10 13857.4660633484 1036.9541855204) (10 13857.4660633484 1044.4937782805))
((0 . "LWPOLYLINE") (100 . "AcDbEntity") (8 . "PLANTS") (62 . 94) (370 . 13) (100 . "AcDbPolyline") (90 . 2) (70 . 0)
(43 . 0.0) (10 13857.4660633484 1044.4937782805) (10 13883.8616515837 1048.2664027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13857.4660633484 1036.9541855204 0.0) (10 13874.6727324463 1034.7796144016 0.0) (10 13869.2519222297
1010.0960070372 0.0) (10 13887.631561086 1010.5571266968 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13891.4027149321 248.8687782805 0.0) (10 13863.0131049822 260.7041010603 0.0) (10 13883.0080960587
293.5625929594 0.0) (10 13861.2372171946 309.1996606335 0.0))
((0 . "LWPOLYLINE") (100 . "AcDbEntity") (8 . "PLANTS") (62 . 94) (370 . 13) (100 . "AcDbPolyline") (90 . 2) (70 . 0)
(43 . 0.0) (10 13863.1221719457 3904.5998868778) (10 13906.4860859729 3902.7149321267))
((0 . "LWPOLYLINE") (100 . "AcDbEntity") (8 . "PLANTS") (62 . 94) (370 . 13) (100 . "AcDbPolyline") (90 . 3) (70 . 0)
(43 . 0.0) (10 13882.3590593307 1147.1590526824) (10 13880.09739819 1074.6606334842) (10 13883.8616515837
1063.3484162896))
((0 . "LWPOLYLINE") (100 . "AcDbEntity") (8 . "PLANTS") (62 . 94) (370 . 13) (100 . "AcDbPolyline") (90 . 3) (70 . 0)
(43 . 0.0) (10 13876.3193438914 3751.8849547511) (10 13887.631561086 3741.6231900452) (10 13925.3393665158
3733.0316742081))
((0 . "LWPOLYLINE") (100 . "AcDbEntity") (8 . "PLANTS") (62 . 94) (370 . 13) (100 . "AcDbPolyline") (90 . 3) (70 . 0)
(43 . 0.0) (10 13876.3193438914 3751.8849547511) (10 13891.5435520362 3774.3554298643) (10 13898.9437782805
3778.2805429864))
((0 . "LWPOLYLINE") (100 . "AcDbEntity") (8 . "PLANTS") (62 . 94) (370 . 13) (100 . "AcDbPolyline") (90 . 3) (70 . 0)
(43 . 0.0) (10 13898.9437782805 422.3218325792) (10 13890.3463800905 444.7929864253) (10 13880.0904977376
448.7188914027))
((0 . "LWPOLYLINE") (100 . "AcDbEntity") (8 . "PLANTS") (62 . 94) (370 . 13) (100 . "AcDbPolyline") (90 . 2) (70 . 0)
(43 . 0.0) (10 13883.8616515837 1048.2664027149) (10 13883.8616515837 1063.3484162896))
((0 . "LWPOLYLINE") (100 . "AcDbEntity") (8 . "PLANTS") (62 . 94) (370 . 13) (100 . "AcDbPolyline") (90 . 2) (70 . 0)
(43 . 0.0) (10 13902.7149321267 1067.1182126697) (10 13883.8616515837 1063.3484162896))
((0 . "LWPOLYLINE") (100 . "AcDbEntity") (8 . "PLANTS") (62 . 94) (370 . 13) (100 . "AcDbPolyline") (90 . 3) (70 . 0)
(43 . 0.0) (10 13887.631561086 1010.5571266968) (10 13895.3286199095 1029.5595022624) (10 13883.8616515837
1048.2664027149))
((0 . "LWPOLYLINE") (100 . "AcDbEntity") (8 . "PLANTS") (62 . 94) (370 . 13) (100 . "AcDbPolyline") (90 . 3) (70 . 0)
(43 . 0.0) (10 13883.8616515837 950.2262443439) (10 13891.4096153846 946.6035067873) (10 13914.0271493213
946.4564479638))
((0 . "LWPOLYLINE") (100 . "AcDbEntity") (8 . "PLANTS") (62 . 94) (370 . 13) (100 . "AcDbPolyline") (90 . 2) (70 . 0)
(43 . 0.0) (10 13883.8616515837 950.2262443439) (10 13887.631561086 961.5384615385))
((0 . "LWPOLYLINE") (100 . "AcDbEntity") (8 . "PLANTS") (62 . 94) (370 . 13) (100 . "AcDbPolyline") (90 . 2) (70 . 0)
(43 . 0.0) (10 13887.631561086 1010.5571266968) (10 13891.4027149321 980.3930995475))
((0 . "LWPOLYLINE") (100 . "AcDbEntity") (8 . "PLANTS") (62 . 94) (370 . 13) (100 . "AcDbPolyline") (90 . 3) (70 . 0)
(43 . 0.0) (10 13887.631561086 346.9089366516) (10 13896.2234162896 297.8874434389) (10 13914.0271493213
275.2630090498))
((0 . "LWPOLYLINE") (100 . "AcDbEntity") (8 . "PLANTS") (62 . 94) (370 . 13) (100 . "AcDbPolyline") (90 . 2) (70 . 0)
(43 . 0.0) (10 13891.4027149321 248.8687782805) (10 13910.2559954751 248.8687782805))
((0 . "LWPOLYLINE") (100 . "AcDbEntity") (8 . "PLANTS") (62 . 94) (370 . 13) (100 . "AcDbPolyline") (90 . 2) (70 . 0)
(43 . 0.0) (10 13898.9437782805 3789.592760181) (10 13898.9437782805 3800.9049773756))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13985.6716063348 3831.0704751131 0.0) (10 13955.3520892837 3836.4456896739 0.0) (10 13905.1984738403
3842.9526525929 0.0) (10 13898.9437782806 3800.9049773755 0.0))
((0 . "LWPOLYLINE") (100 . "AcDbEntity") (8 . "PLANTS") (62 . 94) (370 . 13) (100 . "AcDbPolyline") (90 . 2) (70 . 0)
(43 . 0.0) (10 13898.9437782805 3789.592760181) (10 13898.9437782805 3778.2805429864))
((0 . "LWPOLYLINE") (100 . "AcDbEntity") (8 . "PLANTS") (62 . 94) (370 . 13) (100 . "AcDbPolyline") (90 . 3) (70 . 0)
(43 . 0.0) (10 13936.6515837104 3800.9049773756) (10 13914.0271493213 3790.6494343891) (10 13898.9437782805
3789.592760181))
((0 . "LWPOLYLINE") (100 . "AcDbEntity") (8 . "PLANTS") (62 . 94) (370 . 13) (100 . "AcDbPolyline") (90 . 3) (70 . 0)
(43 . 0.0) (10 13925.3393665158 3748.1150452489) (10 13906.3438914027 3774.3554298643) (10 13898.9437782805
3778.2805429864))
((0 . "LWPOLYLINE") (100 . "AcDbEntity") (8 . "PLANTS") (62 . 94) (370 . 13) (100 . "AcDbPolyline") (90 . 3) (70 . 0)
(43 . 0.0) (10 13940.4227375566 433.6340497738) (10 13925.3393665158 422.4771493213) (10 13898.9437782805
422.3218325792))
((0 . "LWPOLYLINE") (100 . "AcDbEntity") (8 . "PLANTS") (62 . 94) (370 . 13) (100 . "AcDbPolyline") (90 . 3) (70 . 0)
(43 . 0.0) (10 13906.4860859729 3989.4415158371) (10 13902.7218325792 4000.7544117647) (10 13902.7218325792
4066.4107898589))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13906.4860859729 3902.7149321267 0.0) (10 13982.6032504453 3929.4014575921 0.0) (10 13883.588551084
3963.5384508615 0.0) (10 13906.4860859729 3989.4415158371 0.0))
((0 . "LWPOLYLINE") (100 . "AcDbEntity") (8 . "PLANTS") (62 . 94) (370 . 13) (100 . "AcDbPolyline") (90 . 3) (70 . 0)
(43 . 0.0) (10 13906.4860859729 3989.4415158371) (10 13932.8804298643 3993.0580316742) (10 13955.5048642534
3978.1292986425))
((0 . "LWPOLYLINE") (100 . "AcDbEntity") (8 . "PLANTS") (62 . 94) (370 . 13) (100 . "AcDbPolyline") (90 . 2) (70 . 0)
(43 . 0.0) (10 13906.4860859729 3902.7149321267) (10 13906.4860859729 3880.0904977376))
((0 . "LWPOLYLINE") (100 . "AcDbEntity") (8 . "PLANTS") (62 . 94) (370 . 13) (100 . "AcDbPolyline") (90 . 3) (70 . 0)
(43 . 0.0) (10 13968.703280543 3889.517760181) (10 13955.5089366516 3880.2483031674) (10 13906.4860859729
3880.0904977376))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13910.2559954751 248.8687782805 0.0) (10 13920.9089423002 223.058454593 0.0) (10 13958.6495935735
227.9772093225 0.0) (10 13978.1292986425 241.3263574661 0.0))
((0 . "LWPOLYLINE") (100 . "AcDbEntity") (8 . "PLANTS") (62 . 94) (370 . 13) (100 . "AcDbPolyline") (90 . 2) (70 . 0)
(43 . 0.0) (10 13910.2559954751 248.8687782805) (10 13914.0271493213 275.2630090498))
((0 . "LWPOLYLINE") (100 . "AcDbEntity") (8 . "PLANTS") (62 . 94) (370 . 13) (100 . "AcDbPolyline") (90 . 3) (70 . 0)
(43 . 0.0) (10 13914.0271493213 946.4564479638) (10 13915.2313348416 961.531561086) (10 13929.110520362 969.0808823529))
((0 . "LWPOLYLINE") (100 . "AcDbEntity") (8 . "PLANTS") (62 . 94) (370 . 13) (100 . "AcDbPolyline") (90 . 3) (70 . 0)
(43 . 0.0) (10 13914.0271493213 946.4564479638) (10 13932.8804298643 946.6097285068) (10 13944.1926470588
953.996040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13963.0471719457 290.3478506787 0.0) (10 13943.3631299197 296.1078092294 0.0) (10 13933.605843875
272.3535633128 0.0) (10 13914.0271493213 275.2630090498 0.0))
((0 . "LWPOLYLINE") (100 . "AcDbEntity") (8 . "PLANTS") (62 . 94) (370 . 13) (100 . "AcDbPolyline") (90 . 2) (70 . 0)
(43 . 0.0) (10 13929.110520362 343.1363122172) (10 13917.7983031674 316.742081448))
((0 . "LWPOLYLINE") (100 . "AcDbEntity") (8 . "PLANTS") (62 . 94) (370 . 13) (100 . "AcDbPolyline") (90 . 2) (70 . 0)
(43 . 0.0) (10 13925.3393665158 3748.1150452489) (10 13925.3393665158 3733.0316742081))
((0 . "LWPOLYLINE") (100 . "AcDbEntity") (8 . "PLANTS") (62 . 94) (370 . 13) (100 . "AcDbPolyline") (90 . 2) (70 . 0)
(43 . 0.0) (10 13925.3393665158 3748.1150452489) (10 13955.5048642534 3759.4272624434))
((0 . "LWPOLYLINE") (100 . "AcDbEntity") (8 . "PLANTS") (62 . 94) (370 . 13) (100 . "AcDbPolyline") (90 . 3) (70 . 0)
(43 . 0.0) (10 13929.110520362 1078.4304298643) (10 13940.4227375566 1085.9728506787) (10 13940.4227375566
1089.7426470588))
((0 . "LWPOLYLINE") (100 . "AcDbEntity") (8 . "PLANTS") (62 . 94) (370 . 13) (100 . "AcDbPolyline") (90 . 2) (70 . 0)
(43 . 0.0) (10 13929.110520362 969.0808823529) (10 13944.1926470588 953.996040724))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5105358836)
(40 . 0.7336490401) (40 . 1) (40 . 1) (40 . 1) (40 . 1) (10 13963.0471719457 1089.7426470588 0.0) (10 13990.475849307
1081.1048667345 0.0) (10 13997.9178326285 1012.3775648962 0.0) (10 13933.1503331995 1017.6889676421 0.0) (10
13920.5992950648 994.7966044563 0.0) (10 13929.110520362 969.0808823529 0.0))
((0 . "LWPOLYLINE") (100 . "AcDbEntity") (8 . "PLANTS") (62 . 94) (370 . 13) (100 . "AcDbPolyline") (90 . 2) (70 . 0)
(43 . 0.0) (10 13940.4227375566 433.6340497738) (10 13937.9444901584 470.8036720871))
((0 . "LWPOLYLINE") (100 . "AcDbEntity") (8 . "PLANTS") (62 . 94) (370 . 13) (100 . "AcDbPolyline") (90 . 2) (70 . 0)
(43 . 0.0) (10 13968.703280543 3889.517760181) (10 13940.4227375566 3925.3393665158))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13940.4227375566 433.6340497738 0.0) (10 13954.3130038259 454.7742348502 0.0) (10 13986.2253214143
438.8082144809 0.0) (10 13978.1292986425 418.5520361991 0.0))
((0 . "LWPOLYLINE") (100 . "AcDbEntity") (8 . "PLANTS") (62 . 94) (370 . 13) (100 . "AcDbPolyline") (90 . 2) (70 . 0)
(43 . 0.0) (10 13951.7349547511 953.996040724) (10 13944.1926470588 953.996040724))
((0 . "LWPOLYLINE") (100 . "AcDbEntity") (8 . "PLANTS") (62 . 94) (370 . 13) (100 . "AcDbPolyline") (90 . 3) (70 . 0)
(43 . 0.0) (10 13947.963800905 3797.1338235294) (10 13959.2760180995 3797.1338235294) (10 13963.0471719457
3793.3639140271))
((0 . "LWPOLYLINE") (100 . "AcDbEntity") (8 . "PLANTS") (62 . 94) (370 . 13) (100 . "AcDbPolyline") (90 . 2) (70 . 0)
(43 . 0.0) (10 13974.3593891403 935.1442307692) (10 13951.7349547511 953.996040724))
((0 . "LWPOLYLINE") (100 . "AcDbEntity") (8 . "PLANTS") (62 . 94) (370 . 13) (100 . "AcDbPolyline") (90 . 3) (70 . 0)
(43 . 0.0) (10 13951.7349547511 953.996040724) (10 13974.3593891403 971.6527149321) (10 14004.5248868778 972.850678733))
((0 . "LWPOLYLINE") (100 . "AcDbEntity") (8 . "PLANTS") (62 . 94) (370 . 13) (100 . "AcDbPolyline") (90 . 3) (70 . 0)
(43 . 0.0) (10 14015.8371040724 3748.1150452489) (10 14000.7537330317 3748.2628959276) (10 13955.5048642534
3759.4272624434))
((0 . "LWPOLYLINE") (100 . "AcDbEntity") (8 . "PLANTS") (62 . 94) (370 . 13) (100 . "AcDbPolyline") (90 . 2) (70 . 0)
(43 . 0.0) (10 13963.0471719457 3793.3639140271) (10 13955.5048642534 3759.4272624434))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13959.2760180996 4034.6903846154 0.0) (10 13968.5143051347 4003.5014232624 0.0) (10 14009.2290188208
3993.8569792236 0.0) (10 14012.0659502262 3959.2760180995 0.0))
((0 . "LWPOLYLINE") (100 . "AcDbEntity") (8 . "PLANTS") (62 . 94) (370 . 13) (100 . "AcDbPolyline") (90 . 2) (70 . 0)
(43 . 0.0) (10 13989.4415158371 3800.9049773756) (10 13963.0471719457 3793.3639140271))
((0 . "LWPOLYLINE") (100 . "AcDbEntity") (8 . "PLANTS") (62 . 94) (370 . 13) (100 . "AcDbPolyline") (90 . 3) (70 . 0)
(43 . 0.0) (10 13963.0471719457 403.4700226244) (10 13955.6595022624 324.2845022624) (10 13966.817081448
309.1996606335))
((0 . "LWPOLYLINE") (100 . "AcDbEntity") (8 . "PLANTS") (62 . 94) (370 . 13) (100 . "AcDbPolyline") (90 . 3) (70 . 0)
(43 . 0.0) (10 13963.0471719457 290.3478506787) (10 13973.1553167421 279.0356334842) (10 13978.1292986425
241.3263574661))
((0 . "LWPOLYLINE") (100 . "AcDbEntity") (8 . "PLANTS") (62 . 94) (370 . 13) (100 . "AcDbPolyline") (90 . 2) (70 . 0)
(43 . 0.0) (10 13966.817081448 309.1996606335) (10 13963.0471719457 290.3478506787))
((0 . "LWPOLYLINE") (100 . "AcDbEntity") (8 . "PLANTS") (62 . 94) (370 . 13) (100 . "AcDbPolyline") (90 . 3) (70 . 0)
(43 . 0.0) (10 14008.296040724 320.5118778281) (10 13996.9838235294 314.0279411765) (10 13966.817081448 309.1996606335))
((0 . "LWPOLYLINE") (100 . "AcDbEntity") (8 . "PLANTS") (62 . 94) (370 . 13) (100 . "AcDbPolyline") (90 . 3) (70 . 0)
(43 . 0.0) (10 13968.703280543 3889.517760181) (10 13981.8977375566 3881.1496606335) (10 14004.5248868778
3880.0904977376))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13968.703280543 3889.517760181 0.0) (10 13989.1251142434 3910.5693064367 0.0) (10 13976.3697103717
3951.4145146146 0.0) (10 14012.0659502262 3959.2760180995 0.0))
((0 . "LWPOLYLINE") (100 . "AcDbEntity") (8 . "PLANTS") (62 . 94) (370 . 13) (100 . "AcDbPolyline") (90 . 2) (70 . 0)
(43 . 0.0) (10 13974.3593891403 901.2075791855) (10 13974.3593891403 935.1442307692))
((0 . "LWPOLYLINE") (100 . "AcDbEntity") (8 . "PLANTS") (62 . 94) (370 . 13) (100 . "AcDbPolyline") (90 . 3) (70 . 0)
(43 . 0.0) (10 13974.3593891403 935.1442307692) (10 13989.4415158371 935.2975113122) (10 14004.5248868778
942.6838235294))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 13974.3593891403 901.2075791855 0.0) (10 13996.5780791838 892.6879439696 0.0) (10 14027.2623851459
889.4238370674 0.0) (10 14042.2326923077 912.5197963801 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14049.7737556561 237.556561086 0.0) (10 14028.0966671765 223.4786673314 0.0) (10 13999.0632286071
228.8294974373 0.0) (10 13978.1292986425 241.3263574661 0.0))
((0 . "LWPOLYLINE") (100 . "AcDbEntity") (8 . "PLANTS") (62 . 94) (370 . 13) (100 . "AcDbPolyline") (90 . 2) (70 . 0)
(43 . 0.0) (10 13985.6716063348 3831.0704751131) (10 13989.4415158371 3800.9049773756))
((0 . "LWPOLYLINE") (100 . "AcDbEntity") (8 . "PLANTS") (62 . 94) (370 . 13) (100 . "AcDbPolyline") (90 . 3) (70 . 0)
(43 . 0.0) (10 13985.6716063348 3831.0704751131) (10 13995.7866515837 3842.3833710407) (10 14004.5248868778
3880.0904977376))
((0 . "LWPOLYLINE") (100 . "AcDbEntity") (8 . "PLANTS") (62 . 94) (370 . 13) (100 . "AcDbPolyline") (90 . 2) (70 . 0)
(43 . 0.0) (10 13989.4415158371 3800.9049773756) (10 14019.6082579186 3782.0516968326))
((0 . "LWPOLYLINE") (100 . "AcDbEntity") (8 . "PLANTS") (62 . 94) (370 . 13) (100 . "AcDbPolyline") (90 . 2) (70 . 0)
(43 . 0.0) (10 14004.5248868778 3880.0904977376) (10 14023.3781674208 3880.0904977376))
((0 . "LWPOLYLINE") (100 . "AcDbEntity") (8 . "PLANTS") (62 . 94) (370 . 13) (100 . "AcDbPolyline") (90 . 2) (70 . 0)
(43 . 0.0) (10 14004.5248868778 972.850678733) (10 14004.5248868778 942.6838235294))
((0 . "LWPOLYLINE") (100 . "AcDbEntity") (8 . "PLANTS") (62 . 94) (370 . 13) (100 . "AcDbPolyline") (90 . 2) (70 . 0)
(43 . 0.0) (10 14004.5248868778 972.850678733) (10 14015.8371040724 991.7053167421))
((0 . "LWPOLYLINE") (100 . "AcDbEntity") (8 . "PLANTS") (62 . 94) (370 . 13) (100 . "AcDbPolyline") (90 . 2) (70 . 0)
(43 . 0.0) (10 14004.5248868778 942.6838235294) (10 14042.2326923077 912.5197963801))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14004.5248868778 373.3031674208 0.0) (10 14027.599935735 373.620982028 0.0) (10 14011.7882936617
339.463416205 0.0) (10 14034.6903846154 335.596719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14004.5248868778 373.3031674208 0.0) (10 13986.5332420277 360.0382582885 0.0) (10 13991.7224146932
332.0562923191 0.0) (10 14008.296040724 320.5118778281 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14004.5248868778 373.3031674208 0.0) (10 14005.2197805037 394.1016211134 0.0) (10 14003.8951168142
439.2273197456 0.0) (10 14034.6903846154 444.9462669683 0.0))
((0 . "LWPOLYLINE") (100 . "AcDbEntity") (8 . "PLANTS") (62 . 94) (370 . 13) (100 . "AcDbPolyline") (90 . 2) (70 . 0)
(43 . 0.0) (10 14008.296040724 320.5118778281) (10 14034.6903846154 324.2845022624))
((0 . "LWPOLYLINE") (100 . "AcDbEntity") (8 . "PLANTS") (62 . 94) (370 . 13) (100 . "AcDbPolyline") (90 . 3) (70 . 0)
(43 . 0.0) (10 14008.296040724 267.7234162896) (10 14015.8371040724 267.7234162896) (10 14019.6082579186
275.2630090498))
((0 . "LWPOLYLINE") (100 . "AcDbEntity") (8 . "PLANTS") (62 . 94) (370 . 13) (100 . "AcDbPolyline") (90 . 2) (70 . 0)
(43 . 0.0) (10 14012.0659502262 3959.2760180995) (10 14027.149321267 3959.2760180995))
((0 . "LWPOLYLINE") (100 . "AcDbEntity") (8 . "PLANTS") (62 . 94) (370 . 13) (100 . "AcDbPolyline") (90 . 2) (70 . 0)
(43 . 0.0) (10 14018.0995848412 3733.0316742081) (10 14015.8371040724 3748.1150452489))
((0 . "LWPOLYLINE") (100 . "AcDbEntity") (8 . "PLANTS") (62 . 94) (370 . 13) (100 . "AcDbPolyline") (90 . 2) (70 . 0)
(43 . 0.0) (10 14015.8371040724 3748.1150452489) (10 14019.6082579186 3782.0516968326))
((0 . "LWPOLYLINE") (100 . "AcDbEntity") (8 . "PLANTS") (62 . 94) (370 . 13) (100 . "AcDbPolyline") (90 . 2) (70 . 0)
(43 . 0.0) (10 14034.6903846154 991.7053167421) (10 14015.8371040724 991.7053167421))
((0 . "LWPOLYLINE") (100 . "AcDbEntity") (8 . "PLANTS") (62 . 94) (370 . 13) (100 . "AcDbPolyline") (90 . 3) (70 . 0)
(43 . 0.0) (10 14030.9204751131 1040.7239819005) (10 14013.2700226244 1025.6419683258) (10 14015.8371040724
991.7053167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14019.6082579186 3782.0516968326 0.0) (10 14053.5976967499 3793.9384675716 0.0) (10 14077.7063042832
3825.2001941724 0.0) (10 14091.2514705882 3857.4660633484 0.0))
((0 . "LWPOLYLINE") (100 . "AcDbEntity") (8 . "PLANTS") (62 . 94) (370 . 13) (100 . "AcDbPolyline") (90 . 3) (70 . 0)
(43 . 0.0) (10 14023.3781674208 3880.0904977376) (10 14030.9273755656 3876.467760181) (10 14076.1693438914
3876.3193438914))
((0 . "LWPOLYLINE") (100 . "AcDbEntity") (8 . "PLANTS") (62 . 94) (370 . 13) (100 . "AcDbPolyline") (90 . 2) (70 . 0)
(43 . 0.0) (10 14023.3781674208 3880.0904977376) (10 14030.9204751131 3898.9437782805))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14027.149321267 3959.2760180995 0.0) (10 14026.1534003633 3938.2162808791 0.0) (10 14047.1169405958
3917.7636646836 0.0) (10 14068.6270361991 3925.3393665158 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14027.149321267 3959.2760180995 0.0) (10 14049.4232647559 3974.1456878928 0.0) (10 14066.1012625702
3942.1365841726 0.0) (10 14068.6270361991 3925.3393665158 0.0))
((0 . "LWPOLYLINE") (100 . "AcDbEntity") (8 . "PLANTS") (62 . 94) (370 . 13) (100 . "AcDbPolyline") (90 . 2) (70 . 0)
(43 . 0.0) (10 14029.2695454963 3671.6394972026) (10 14034.6903846154 3668.9295248869))
((0 . "LWPOLYLINE") (100 . "AcDbEntity") (8 . "PLANTS") (62 . 94) (370 . 13) (100 . "AcDbPolyline") (90 . 2) (70 . 0)
(43 . 0.0) (10 14030.9204751131 1048.2664027149) (10 14030.9204751131 1040.7239819005))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14034.6903846154 991.7053167421 0.0) (10 14045.7342492578 1005.510677956 0.0) (10 14047.9031607808
1029.8162355164 0.0) (10 14030.9204751131 1040.7239819005 0.0))
((0 . "LWPOLYLINE") (100 . "AcDbEntity") (8 . "PLANTS") (62 . 94) (370 . 13) (100 . "AcDbPolyline") (90 . 3) (70 . 0)
(43 . 0.0) (10 14064.8571266968 3642.5339366516) (10 14042.3874434389 3651.1316742081) (10 14034.6903846154
3668.9295248869))
((0 . "LWPOLYLINE") (100 . "AcDbEntity") (8 . "PLANTS") (62 . 94) (370 . 13) (100 . "AcDbPolyline") (90 . 2) (70 . 0)
(43 . 0.0) (10 14061.0859728507 3684.0116515837) (10 14034.6903846154 3668.9295248869))
((0 . "LWPOLYLINE") (100 . "AcDbEntity") (8 . "PLANTS") (62 . 94) (370 . 13) (100 . "AcDbPolyline") (90 . 2) (70 . 0)
(43 . 0.0) (10 14042.2326923077 3604.8268099548) (10 14034.6903846154 3612.367760181))
((0 . "LWPOLYLINE") (100 . "AcDbEntity") (8 . "PLANTS") (62 . 94) (370 . 13) (100 . "AcDbPolyline") (90 . 2) (70 . 0)
(43 . 0.0) (10 14034.6903846154 991.7053167421) (10 14061.0859728507 984.1628959276))
((0 . "LWPOLYLINE") (100 . "AcDbEntity") (8 . "PLANTS") (62 . 94) (370 . 13) (100 . "AcDbPolyline") (90 . 3) (70 . 0)
(43 . 0.0) (10 14034.6903846154 444.9462669683) (10 14042.0849547511 422.3218325792) (10 14046.00260181 343.1363122172))
((0 . "LWPOLYLINE") (100 . "AcDbEntity") (8 . "PLANTS") (62 . 94) (370 . 13) (100 . "AcDbPolyline") (90 . 3) (70 . 0)
(43 . 0.0) (10 14034.6903846154 444.9462669683) (10 14042.3805429864 460.0311085973) (10 14064.8571266968
482.6555429864))
((0 . "LWPOLYLINE") (100 . "AcDbEntity") (8 . "PLANTS") (62 . 94) (370 . 13) (100 . "AcDbPolyline") (90 . 2) (70 . 0)
(43 . 0.0) (10 14034.6903846154 324.2845022624) (10 14034.6903846154 335.596719457))
((0 . "LWPOLYLINE") (100 . "AcDbEntity") (8 . "PLANTS") (62 . 94) (370 . 13) (100 . "AcDbPolyline") (90 . 2) (70 . 0)
(43 . 0.0) (10 14034.6903846154 335.596719457) (10 14046.00260181 343.1363122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14117.6470588235 256.411199095 0.0) (10 14095.0999956056 286.0489315352 0.0) (10 14049.4948561984
283.8265151377 0.0) (10 14034.6903846154 324.2845022624 0.0))
((0 . "LWPOLYLINE") (100 . "AcDbEntity") (8 . "PLANTS") (62 . 94) (370 . 13) (100 . "AcDbPolyline") (90 . 2) (70 . 0)
(43 . 0.0) (10 14061.0859728507 1116.1397058824) (10 14042.2326923077 1089.7426470588))
((0 . "LWPOLYLINE") (100 . "AcDbEntity") (8 . "PLANTS") (62 . 94) (370 . 13) (100 . "AcDbPolyline") (90 . 2) (70 . 0)
(43 . 0.0) (10 14042.2326923077 912.5197963801) (10 14061.0859728507 912.5197963801))
((0 . "LWPOLYLINE") (100 . "AcDbEntity") (8 . "PLANTS") (62 . 94) (370 . 13) (100 . "AcDbPolyline") (90 . 2) (70 . 0)
(43 . 0.0) (10 14087.481561086 345.0226244344) (10 14046.00260181 343.1363122172))
((0 . "LWPOLYLINE") (100 . "AcDbEntity") (8 . "PLANTS") (62 . 94) (370 . 13) (100 . "AcDbPolyline") (90 . 3) (70 . 0)
(43 . 0.0) (10 14091.2514705882 3993.2126696833) (10 14072.4050904977 4001.8041855204) (10 14049.7737556561
4023.3781674208))
((0 . "LWPOLYLINE") (100 . "AcDbEntity") (8 . "PLANTS") (62 . 94) (370 . 13) (100 . "AcDbPolyline") (90 . 2) (70 . 0)
(43 . 0.0) (10 14049.7737556561 256.411199095) (10 14049.7737556561 237.556561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14117.6470588235 256.411199095 0.0) (10 14105.8061541206 232.0008429373 0.0) (10 14071.7180403849
224.1643711744 0.0) (10 14049.7737556561 237.556561086 0.0))
((0 . "LWPOLYLINE") (100 . "AcDbEntity") (8 . "PLANTS") (62 . 94) (370 . 13) (100 . "AcDbPolyline") (90 . 2) (70 . 0)
(43 . 0.0) (10 14061.0859728507 3684.0116515837) (10 14076.1693438914 3684.0116515837))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2962232256)
(40 . 0.4642854983) (40 . 1) (40 . 1) (40 . 1) (40 . 1) (10 14196.8325791855 3748.1150452489 0.0) (10 14171.8767419025
3747.3926090327 0.0) (10 14156.5182819916 3801.1696610304 0.0) (10 14075.9872533522 3799.0652280891 0.0) (10
14049.7358531685 3719.4143378083 0.0) (10 14061.0859728507 3684.0116515838 0.0))
((0 . "LWPOLYLINE") (100 . "AcDbEntity") (8 . "PLANTS") (62 . 94) (370 . 13) (100 . "AcDbPolyline") (90 . 2) (70 . 0)
(43 . 0.0) (10 14061.0859728507 984.1628959276) (10 14061.0859728507 912.5197963801))
((0 . "LWPOLYLINE") (100 . "AcDbEntity") (8 . "PLANTS") (62 . 94) (370 . 13) (100 . "AcDbPolyline") (90 . 3) (70 . 0)
(43 . 0.0) (10 14061.0859728507 984.1628959276) (10 14079.9323529412 989.1237556561) (10 14087.481561086
995.4751131222))
((0 . "LWPOLYLINE") (100 . "AcDbEntity") (8 . "PLANTS") (62 . 94) (370 . 13) (100 . "AcDbPolyline") (90 . 2) (70 . 0)
(43 . 0.0) (10 14095.0226244344 912.5197963801) (10 14061.0859728507 912.5197963801))
((0 . "LWPOLYLINE") (100 . "AcDbEntity") (8 . "PLANTS") (62 . 94) (370 . 13) (100 . "AcDbPolyline") (90 . 2) (70 . 0)
(43 . 0.0) (10 14076.1693438914 3925.3393665158) (10 14068.6270361991 3925.3393665158))
((0 . "LWPOLYLINE") (100 . "AcDbEntity") (8 . "PLANTS") (62 . 94) (370 . 13) (100 . "AcDbPolyline") (90 . 2) (70 . 0)
(43 . 0.0) (10 14076.1693438914 3925.3393665158) (10 14076.1693438914 3876.3193438914))
((0 . "LWPOLYLINE") (100 . "AcDbEntity") (8 . "PLANTS") (62 . 94) (370 . 13) (100 . "AcDbPolyline") (90 . 2) (70 . 0)
(43 . 0.0) (10 14106.334841629 3929.110520362) (10 14076.1693438914 3925.3393665158))
((0 . "LWPOLYLINE") (100 . "AcDbEntity") (8 . "PLANTS") (62 . 94) (370 . 13) (100 . "AcDbPolyline") (90 . 2) (70 . 0)
(43 . 0.0) (10 14076.1693438914 3876.3193438914) (10 14091.2514705882 3857.4660633484))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14076.1693438914 3684.0116515837 0.0) (10 14068.6114468704 3652.9510285396 0.0) (10 14105.9637447932
3642.3580113804 0.0) (10 14121.4182126697 3665.1583710407 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7209979863) (40
. 1) (40 . 1) (40 . 1) (40 . 1) (10 14076.1693438915 3684.0116515837 0.0) (10 14100.0490292436 3683.6970123464 0.0) (10
14114.8629891177 3736.5754340066 0.0) (10 14145.0424349241 3732.6325640858 0.0) (10 14151.5837104074 3721.7194570136
0.0))
((0 . "LWPOLYLINE") (100 . "AcDbEntity") (8 . "PLANTS") (62 . 94) (370 . 13) (100 . "AcDbPolyline") (90 . 3) (70 . 0)
(43 . 0.0) (10 14076.1693438914 1014.3297511312) (10 14077.3735294118 1006.7811085973) (10 14087.481561086
995.4751131222))
((0 . "LWPOLYLINE") (100 . "AcDbEntity") (8 . "PLANTS") (62 . 94) (370 . 13) (100 . "AcDbPolyline") (90 . 2) (70 . 0)
(43 . 0.0) (10 14087.481561086 995.4751131222) (10 14102.5636877828 995.4751131222))
((0 . "LWPOLYLINE") (100 . "AcDbEntity") (8 . "PLANTS") (62 . 94) (370 . 13) (100 . "AcDbPolyline") (90 . 3) (70 . 0)
(43 . 0.0) (10 14091.2514705882 328.0542986425) (10 14087.481561086 331.8240950226) (10 14087.481561086 345.0226244344))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14128.9592760181 426.0944570136 0.0) (10 14089.3849575817 430.6769959569 0.0) (10 14064.0748123647
374.7287631693 0.0) (10 14087.481561086 345.0226244344 0.0))
((0 . "LWPOLYLINE") (100 . "AcDbEntity") (8 . "PLANTS") (62 . 94) (370 . 13) (100 . "AcDbPolyline") (90 . 2) (70 . 0)
(43 . 0.0) (10 14113.8759049774 354.4485294118) (10 14087.481561086 345.0226244344))
((0 . "LWPOLYLINE") (100 . "AcDbEntity") (8 . "PLANTS") (62 . 94) (370 . 13) (100 . "AcDbPolyline") (90 . 2) (70 . 0)
(43 . 0.0) (10 14110.1059954751 4019.6082579186) (10 14091.2514705882 4064.8571266968))
((0 . "LWPOLYLINE") (100 . "AcDbEntity") (8 . "PLANTS") (62 . 94) (370 . 13) (100 . "AcDbPolyline") (90 . 3) (70 . 0)
(43 . 0.0) (10 14091.2514705882 3993.2126696833) (10 14096.2268099548 3951.7411764706) (10 14106.334841629
3944.1926470588))
((0 . "LWPOLYLINE") (100 . "AcDbEntity") (8 . "PLANTS") (62 . 94) (370 . 13) (100 . "AcDbPolyline") (90 . 2) (70 . 0)
(43 . 0.0) (10 14091.2514705882 3993.2126696833) (10 14110.1059954751 4019.6082579186))
((0 . "LWPOLYLINE") (100 . "AcDbEntity") (8 . "PLANTS") (62 . 94) (370 . 13) (100 . "AcDbPolyline") (90 . 2) (70 . 0)
(43 . 0.0) (10 14128.9592760181 3861.2372171946) (10 14091.2514705882 3857.4660633484))
((0 . "LWPOLYLINE") (100 . "AcDbEntity") (8 . "PLANTS") (62 . 94) (370 . 13) (100 . "AcDbPolyline") (90 . 3) (70 . 0)
(43 . 0.0) (10 14095.0226244344 912.5197963801) (10 14102.5705882353 905.1320135747) (10 14144.0426470588
904.9773755656))
((0 . "LWPOLYLINE") (100 . "AcDbEntity") (8 . "PLANTS") (62 . 94) (370 . 13) (100 . "AcDbPolyline") (90 . 3) (70 . 0)
(43 . 0.0) (10 14095.0226244344 912.5197963801) (10 14106.1802036199 931.3716063348) (10 14106.334841629
991.7053167421))
((0 . "LWPOLYLINE") (100 . "AcDbEntity") (8 . "PLANTS") (62 . 94) (370 . 13) (100 . "AcDbPolyline") (90 . 2) (70 . 0)
(43 . 0.0) (10 14102.5636877828 1025.6419683258) (10 14102.5636877828 995.4751131222))
((0 . "LWPOLYLINE") (100 . "AcDbEntity") (8 . "PLANTS") (62 . 94) (370 . 13) (100 . "AcDbPolyline") (90 . 2) (70 . 0)
(43 . 0.0) (10 14106.334841629 991.7053167421) (10 14102.5636877828 995.4751131222))
((0 . "LWPOLYLINE") (100 . "AcDbEntity") (8 . "PLANTS") (62 . 94) (370 . 13) (100 . "AcDbPolyline") (90 . 3) (70 . 0)
(43 . 0.0) (10 14106.334841629 991.7053167421) (10 14102.5636877828 991.7053167421) (10 14102.5636877828
995.4751131222))
((0 . "LWPOLYLINE") (100 . "AcDbEntity") (8 . "PLANTS") (62 . 94) (370 . 13) (100 . "AcDbPolyline") (90 . 2) (70 . 0)
(43 . 0.0) (10 14106.334841629 3929.110520362) (10 14106.334841629 3944.1926470588))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2538583635)
(40 . 0.3278243102) (40 . 1) (40 . 1) (40 . 1) (40 . 1) (10 14110.1059954751 4019.6082579185 0.0) (10 14123.2475747826
4017.949412989 0.0) (10 14138.5139144228 4045.6598073566 0.0) (10 14176.7394540051 4020.9485829301 0.0) (10
14125.0052260505 3934.8908175631 0.0) (10 14106.334841629 3944.1926470588 0.0))
((0 . "LWPOLYLINE") (100 . "AcDbEntity") (8 . "PLANTS") (62 . 94) (370 . 13) (100 . "AcDbPolyline") (90 . 3) (70 . 0)
(43 . 0.0) (10 14106.334841629 3929.110520362) (10 14125.1881221719 3917.6498868778) (10 14142.1564479638
3900.8299773756))
((0 . "LWPOLYLINE") (100 . "AcDbEntity") (8 . "PLANTS") (62 . 94) (370 . 13) (100 . "AcDbPolyline") (90 . 3) (70 . 0)
(43 . 0.0) (10 14140.2714932127 976.6204751131) (10 14117.6470588235 990.5004524887) (10 14106.334841629
991.7053167421))
((0 . "LWPOLYLINE") (100 . "AcDbEntity") (8 . "PLANTS") (62 . 94) (370 . 13) (100 . "AcDbPolyline") (90 . 2) (70 . 0)
(43 . 0.0) (10 14110.1059954751 380.8455882353) (10 14113.8759049774 354.4485294118))
((0 . "LWPOLYLINE") (100 . "AcDbEntity") (8 . "PLANTS") (62 . 94) (370 . 13) (100 . "AcDbPolyline") (90 . 2) (70 . 0)
(43 . 0.0) (10 14140.2714932127 354.4485294118) (10 14113.8759049774 354.4485294118))
((0 . "LWPOLYLINE") (100 . "AcDbEntity") (8 . "PLANTS") (62 . 94) (370 . 13) (100 . "AcDbPolyline") (90 . 2) (70 . 0)
(43 . 0.0) (10 14128.9592760181 260.1809954751) (10 14117.6470588235 256.411199095))
((0 . "LWPOLYLINE") (100 . "AcDbEntity") (8 . "PLANTS") (62 . 94) (370 . 13) (100 . "AcDbPolyline") (90 . 3) (70 . 0)
(43 . 0.0) (10 14140.2714932127 3684.0116515837) (10 14125.342760181 3676.3225113122) (10 14121.4182126697
3665.1583710407))
((0 . "LWPOLYLINE") (100 . "AcDbEntity") (8 . "PLANTS") (62 . 94) (370 . 13) (100 . "AcDbPolyline") (90 . 3) (70 . 0)
(43 . 0.0) (10 14121.4182126697 3665.1583710407) (10 14136.493438914 3666.3559954751) (10 14144.0426470588
3672.6994343891))
((0 . "LWPOLYLINE") (100 . "AcDbEntity") (8 . "PLANTS") (62 . 94) (370 . 13) (100 . "AcDbPolyline") (90 . 2) (70 . 0)
(43 . 0.0) (10 14121.4182126697 275.2630090498) (10 14121.4182126697 282.8054298643))
((0 . "LWPOLYLINE") (100 . "AcDbEntity") (8 . "PLANTS") (62 . 94) (370 . 13) (100 . "AcDbPolyline") (90 . 3) (70 . 0)
(43 . 0.0) (10 14121.4182126697 275.2630090498) (10 14113.8759049774 279.0356334842) (10 14121.4182126697
282.8054298643))
((0 . "LWPOLYLINE") (100 . "AcDbEntity") (8 . "PLANTS") (62 . 94) (370 . 13) (100 . "AcDbPolyline") (90 . 3) (70 . 0)
(43 . 0.0) (10 14121.4182126697 282.8054298643) (10 14133.9277149321 309.1996606335) (10 14147.8125565611
324.2845022624))
((0 . "LWPOLYLINE") (100 . "AcDbEntity") (8 . "PLANTS") (62 . 94) (370 . 13) (100 . "AcDbPolyline") (90 . 3) (70 . 0)
(43 . 0.0) (10 14128.9592760181 260.1809954751) (10 14121.4182126697 267.7234162896) (10 14121.4182126697
275.2630090498))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14200.6037330317 3808.446040724 0.0) (10 14171.1843694176 3809.534097848 0.0) (10 14133.4476811031
3828.8702462025 0.0) (10 14128.9592760181 3861.2372171946 0.0))
((0 . "LWPOLYLINE") (100 . "AcDbEntity") (8 . "PLANTS") (62 . 94) (370 . 13) (100 . "AcDbPolyline") (90 . 3) (70 . 0)
(43 . 0.0) (10 14142.1564479638 3900.8299773756) (10 14130.0087104072 3876.3193438914) (10 14128.9592760181
3861.2372171946))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14128.9592760181 426.0944570136 0.0) (10 14121.5411962172 411.4651823705 0.0) (10 14134.1469965247
388.0565262789 0.0) (10 14151.5837104072 392.1578054299 0.0))
((0 . "LWPOLYLINE") (100 . "AcDbEntity") (8 . "PLANTS") (62 . 94) (370 . 13) (100 . "AcDbPolyline") (90 . 3) (70 . 0)
(43 . 0.0) (10 14128.9592760181 426.0944570136) (10 14136.507239819 436.2018099548) (10 14159.1247737557
437.4066742081))
((0 . "LWPOLYLINE") (100 . "AcDbEntity") (8 . "PLANTS") (62 . 94) (370 . 13) (100 . "AcDbPolyline") (90 . 2) (70 . 0)
(43 . 0.0) (10 14144.0426470588 260.1809954751) (10 14128.9592760181 260.1809954751))
((0 . "LWPOLYLINE") (100 . "AcDbEntity") (8 . "PLANTS") (62 . 94) (370 . 13) (100 . "AcDbPolyline") (90 . 2) (70 . 0)
(43 . 0.0) (10 14140.2714932127 3684.0116515837) (10 14144.0426470588 3672.6994343891))
((0 . "LWPOLYLINE") (100 . "AcDbEntity") (8 . "PLANTS") (62 . 94) (370 . 13) (100 . "AcDbPolyline") (90 . 2) (70 . 0)
(43 . 0.0) (10 14151.5837104072 3721.7194570136) (10 14140.2714932127 3684.0116515837))
((0 . "LWPOLYLINE") (100 . "AcDbEntity") (8 . "PLANTS") (62 . 94) (370 . 13) (100 . "AcDbPolyline") (90 . 2) (70 . 0)
(43 . 0.0) (10 14151.5837104072 950.2262443439) (10 14140.2714932127 976.6204751131))
((0 . "LWPOLYLINE") (100 . "AcDbEntity") (8 . "PLANTS") (62 . 94) (370 . 13) (100 . "AcDbPolyline") (90 . 2) (70 . 0)
(43 . 0.0) (10 14166.667081448 995.4751131222) (10 14140.2714932127 976.6204751131))
((0 . "LWPOLYLINE") (100 . "AcDbEntity") (8 . "PLANTS") (62 . 94) (370 . 13) (100 . "AcDbPolyline") (90 . 2) (70 . 0)
(43 . 0.0) (10 14140.2714932127 354.4485294118) (10 14147.8125565611 324.2845022624))
((0 . "LWPOLYLINE") (100 . "AcDbEntity") (8 . "PLANTS") (62 . 94) (370 . 13) (100 . "AcDbPolyline") (90 . 2) (70 . 0)
(43 . 0.0) (10 14151.5837104072 392.1578054299) (10 14140.2714932127 354.4485294118))
((0 . "LWPOLYLINE") (100 . "AcDbEntity") (8 . "PLANTS") (62 . 94) (370 . 13) (100 . "AcDbPolyline") (90 . 3) (70 . 0)
(43 . 0.0) (10 14142.1564479638 3900.8299773756) (10 14159.1247737557 3885.0654977376) (10 14200.6037330317
3883.8616515837))
((0 . "LWPOLYLINE") (100 . "AcDbEntity") (8 . "PLANTS") (62 . 94) (370 . 13) (100 . "AcDbPolyline") (90 . 2) (70 . 0)
(43 . 0.0) (10 14155.3548642534 3917.7983031674) (10 14142.1564479638 3900.8299773756))
((0 . "LWPOLYLINE") (100 . "AcDbEntity") (8 . "PLANTS") (62 . 94) (370 . 13) (100 . "AcDbPolyline") (90 . 2) (70 . 0)
(43 . 0.0) (10 14144.0426470588 3672.6994343891) (10 14159.1247737557 3668.9295248869))
((0 . "LWPOLYLINE") (100 . "AcDbEntity") (8 . "PLANTS") (62 . 94) (370 . 13) (100 . "AcDbPolyline") (90 . 2) (70 . 0)
(43 . 0.0) (10 14144.0426470588 904.9773755656) (10 14177.9792986425 904.9773755656))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14144.0426470588 904.9773755656 0.0) (10 14140.7213776825 918.9914018904 0.0) (10 14138.2120905905
939.8310162688 0.0) (10 14151.5837104072 950.2262443439 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14144.0426470588 260.1809954751 0.0) (10 14159.8154940938 215.5351507529 0.0) (10 14226.7647957548
217.3180975666 0.0) (10 14260.9347285068 241.3263574661 0.0))
((0 . "LWPOLYLINE") (100 . "AcDbEntity") (8 . "PLANTS") (62 . 94) (370 . 13) (100 . "AcDbPolyline") (90 . 2) (70 . 0)
(43 . 0.0) (10 14144.0426470588 260.1809954751) (10 14155.3548642534 271.4932126697))
((0 . "LWPOLYLINE") (100 . "AcDbEntity") (8 . "PLANTS") (62 . 94) (370 . 13) (100 . "AcDbPolyline") (90 . 2) (70 . 0)
(43 . 0.0) (10 14159.1247737557 324.2845022624) (10 14147.8125565611 324.2845022624))
((0 . "LWPOLYLINE") (100 . "AcDbEntity") (8 . "PLANTS") (62 . 94) (370 . 13) (100 . "AcDbPolyline") (90 . 2) (70 . 0)
(43 . 0.0) (10 14151.5837104072 3721.7194570136) (10 14159.1247737557 3721.7194570136))
((0 . "LWPOLYLINE") (100 . "AcDbEntity") (8 . "PLANTS") (62 . 94) (370 . 13) (100 . "AcDbPolyline") (90 . 2) (70 . 0)
(43 . 0.0) (10 14159.1247737557 950.2262443439) (10 14151.5837104072 950.2262443439))
((0 . "LWPOLYLINE") (100 . "AcDbEntity") (8 . "PLANTS") (62 . 94) (370 . 13) (100 . "AcDbPolyline") (90 . 2) (70 . 0)
(43 . 0.0) (10 14151.5837104072 392.1578054299) (10 14159.1247737557 414.782239819))
((0 . "LWPOLYLINE") (100 . "AcDbEntity") (8 . "PLANTS") (62 . 94) (370 . 13) (100 . "AcDbPolyline") (90 . 2) (70 . 0)
(43 . 0.0) (10 14155.3548642534 3917.7983031674) (10 14189.2915158371 3917.7983031674))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14155.3548642534 3917.7983031674 0.0) (10 14154.1844398571 3937.8002563899 0.0) (10 14165.6972689175
3965.9637395951 0.0) (10 14189.2915158371 3966.817081448 0.0))
((0 . "LWPOLYLINE") (100 . "AcDbEntity") (8 . "PLANTS") (62 . 94) (370 . 13) (100 . "AcDbPolyline") (90 . 3) (70 . 0)
(43 . 0.0) (10 14166.667081448 995.4751131222) (10 14161.6987556561 1014.1744343891) (10 14155.3548642534
1018.0995475113))
((0 . "LWPOLYLINE") (100 . "AcDbEntity") (8 . "PLANTS") (62 . 94) (370 . 13) (100 . "AcDbPolyline") (90 . 2) (70 . 0)
(43 . 0.0) (10 14177.9792986425 452.4886877828) (10 14155.3548642534 478.882918552))
((0 . "LWPOLYLINE") (100 . "AcDbEntity") (8 . "PLANTS") (62 . 94) (370 . 13) (100 . "AcDbPolyline") (90 . 2) (70 . 0)
(43 . 0.0) (10 14155.3548642534 271.4932126697) (10 14159.1247737557 324.2845022624))
((0 . "LWPOLYLINE") (100 . "AcDbEntity") (8 . "PLANTS") (62 . 94) (370 . 13) (100 . "AcDbPolyline") (90 . 3) (70 . 0)
(43 . 0.0) (10 14181.7492081448 279.0356334842) (10 14170.4369909502 272.5495475113) (10 14155.3548642534
271.4932126697))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14159.1247737557 950.2262443439 0.0) (10 14173.1245480827 943.5771688371 0.0) (10 14159.2594352638
922.6980652516 0.0) (10 14177.9792986425 920.0593891403 0.0))
((0 . "LWPOLYLINE") (100 . "AcDbEntity") (8 . "PLANTS") (62 . 94) (370 . 13) (100 . "AcDbPolyline") (90 . 2) (70 . 0)
(43 . 0.0) (10 14159.1247737557 950.2262443439) (10 14181.7492081448 972.850678733))
((0 . "LWPOLYLINE") (100 . "AcDbEntity") (8 . "PLANTS") (62 . 94) (370 . 13) (100 . "AcDbPolyline") (90 . 2) (70 . 0)
(43 . 0.0) (10 14159.1247737557 437.4066742081) (10 14159.1247737557 414.782239819))
((0 . "LWPOLYLINE") (100 . "AcDbEntity") (8 . "PLANTS") (62 . 94) (370 . 13) (100 . "AcDbPolyline") (90 . 2) (70 . 0)
(43 . 0.0) (10 14177.9792986425 452.4886877828) (10 14159.1247737557 437.4066742081))
((0 . "LWPOLYLINE") (100 . "AcDbEntity") (8 . "PLANTS") (62 . 94) (370 . 13) (100 . "AcDbPolyline") (90 . 2) (70 . 0)
(43 . 0.0) (10 14159.1247737557 414.782239819) (10 14185.520361991 403.4700226244))
((0 . "LWPOLYLINE") (100 . "AcDbEntity") (8 . "PLANTS") (62 . 94) (370 . 13) (100 . "AcDbPolyline") (90 . 2) (70 . 0)
(43 . 0.0) (10 14189.2915158371 331.8240950226) (10 14159.1247737557 324.2845022624))
((0 . "LWPOLYLINE") (100 . "AcDbEntity") (8 . "PLANTS") (62 . 94) (370 . 13) (100 . "AcDbPolyline") (90 . 2) (70 . 0)
(43 . 0.0) (10 14166.667081448 3601.0555429864) (10 14177.9792986425 3616.1390271493))
((0 . "LWPOLYLINE") (100 . "AcDbEntity") (8 . "PLANTS") (62 . 94) (370 . 13) (100 . "AcDbPolyline") (90 . 2) (70 . 0)
(43 . 0.0) (10 14166.667081448 995.4751131222) (10 14181.7492081448 972.850678733))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.2822629141)
(40 . 0.4387075103) (40 . 0.6201777528) (40 . 1) (40 . 1) (40 . 1) (40 . 1) (10 14196.8325791856 3748.1150452489 0.0)
(10 14208.5371764217 3736.4439073533 0.0) (10 14213.0795187833 3715.2817726362 0.0) (10 14231.857183886 3681.4274141453
0.0) (10 14237.2278286071 3635.8874270963 0.0) (10 14187.4367395966 3647.6120919973 0.0) (10 14174.2081447964
3661.3872171946 0.0))
((0 . "LWPOLYLINE") (100 . "AcDbEntity") (8 . "PLANTS") (62 . 94) (370 . 13) (100 . "AcDbPolyline") (90 . 2) (70 . 0)
(43 . 0.0) (10 14177.9792986425 904.9773755656) (10 14177.9792986425 920.0593891403))
((0 . "LWPOLYLINE") (100 . "AcDbEntity") (8 . "PLANTS") (62 . 94) (370 . 13) (100 . "AcDbPolyline") (90 . 3) (70 . 0)
(43 . 0.0) (10 14196.8325791855 957.7686651584) (10 14188.0874434389 931.3716063348) (10 14177.9792986425
920.0593891403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14294.8713800905 904.9773755656 0.0) (10 14256.8530120097 896.0982640821 0.0) (10 14215.7151404037
894.1694909493 0.0) (10 14177.9792986425 904.9773755656 0.0))
((0 . "LWPOLYLINE") (100 . "AcDbEntity") (8 . "PLANTS") (62 . 94) (370 . 13) (100 . "AcDbPolyline") (90 . 2) (70 . 0)
(43 . 0.0) (10 14177.9792986425 452.4886877828) (10 14189.2915158371 452.4886877828))
((0 . "LWPOLYLINE") (100 . "AcDbEntity") (8 . "PLANTS") (62 . 94) (370 . 13) (100 . "AcDbPolyline") (90 . 2) (70 . 0)
(43 . 0.0) (10 14181.7492081448 972.850678733) (10 14196.8325791855 972.850678733))
((0 . "LWPOLYLINE") (100 . "AcDbEntity") (8 . "PLANTS") (62 . 94) (370 . 13) (100 . "AcDbPolyline") (90 . 2) (70 . 0)
(43 . 0.0) (10 14193.0614253394 350.6787330317) (10 14185.520361991 403.4700226244))
((0 . "LWPOLYLINE") (100 . "AcDbEntity") (8 . "PLANTS") (62 . 94) (370 . 13) (100 . "AcDbPolyline") (90 . 2) (70 . 0)
(43 . 0.0) (10 14189.2915158371 414.782239819) (10 14185.520361991 403.4700226244))
((0 . "LWPOLYLINE") (100 . "AcDbEntity") (8 . "PLANTS") (62 . 94) (370 . 13) (100 . "AcDbPolyline") (90 . 3) (70 . 0)
(43 . 0.0) (10 14189.2915158371 3917.7983031674) (10 14196.6779411765 3944.1926470588) (10 14189.2915158371
3966.817081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14249.6225113122 4004.5248868779 0.0) (10 14224.1788153819 4016.454204818 0.0) (10 14203.1397253327
3983.4498514785 0.0) (10 14189.2915158371 3966.817081448 0.0))
((0 . "LWPOLYLINE") (100 . "AcDbEntity") (8 . "PLANTS") (62 . 94) (370 . 13) (100 . "AcDbPolyline") (90 . 2) (70 . 0)
(43 . 0.0) (10 14189.2915158371 3917.7983031674) (10 14200.6037330317 3910.2559954751))
((0 . "LWPOLYLINE") (100 . "AcDbEntity") (8 . "PLANTS") (62 . 94) (370 . 13) (100 . "AcDbPolyline") (90 . 2) (70 . 0)
(43 . 0.0) (10 14193.0614253394 3691.553959276) (10 14189.2915158371 3714.1783936652))
((0 . "LWPOLYLINE") (100 . "AcDbEntity") (8 . "PLANTS") (62 . 94) (370 . 13) (100 . "AcDbPolyline") (90 . 2) (70 . 0)
(43 . 0.0) (10 14189.2915158371 527.9044117647) (10 14189.2915158371 520.3619909502))
((0 . "LWPOLYLINE") (100 . "AcDbEntity") (8 . "PLANTS") (62 . 94) (370 . 13) (100 . "AcDbPolyline") (90 . 2) (70 . 0)
(43 . 0.0) (10 14215.6858597285 520.3619909502) (10 14189.2915158371 520.3619909502))
((0 . "LWPOLYLINE") (100 . "AcDbEntity") (8 . "PLANTS") (62 . 94) (370 . 13) (100 . "AcDbPolyline") (90 . 2) (70 . 0)
(43 . 0.0) (10 14193.0614253394 486.4253393665) (10 14189.2915158371 520.3619909502))
((0 . "LWPOLYLINE") (100 . "AcDbEntity") (8 . "PLANTS") (62 . 94) (370 . 13) (100 . "AcDbPolyline") (90 . 3) (70 . 0)
(43 . 0.0) (10 14211.9159502262 429.8642533937) (10 14196.839479638 441.1826923077) (10 14189.2915158371
452.4886877828))
((0 . "LWPOLYLINE") (100 . "AcDbEntity") (8 . "PLANTS") (62 . 94) (370 . 13) (100 . "AcDbPolyline") (90 . 2) (70 . 0)
(43 . 0.0) (10 14193.0614253394 486.4253393665) (10 14189.2915158371 452.4886877828))
((0 . "LWPOLYLINE") (100 . "AcDbEntity") (8 . "PLANTS") (62 . 94) (370 . 13) (100 . "AcDbPolyline") (90 . 3) (70 . 0)
(43 . 0.0) (10 14189.2915158371 331.8240950226) (10 14193.0545248869 320.5118778281) (10 14189.2915158371
305.4298642534))
((0 . "LWPOLYLINE") (100 . "AcDbEntity") (8 . "PLANTS") (62 . 94) (370 . 13) (100 . "AcDbPolyline") (90 . 2) (70 . 0)
(43 . 0.0) (10 14193.0614253394 350.6787330317) (10 14189.2915158371 331.8240950226))
((0 . "LWPOLYLINE") (100 . "AcDbEntity") (8 . "PLANTS") (62 . 94) (370 . 13) (100 . "AcDbPolyline") (90 . 2) (70 . 0)
(43 . 0.0) (10 14193.0614253394 3691.553959276) (10 14193.0614253394 3684.0116515837))
((0 . "LWPOLYLINE") (100 . "AcDbEntity") (8 . "PLANTS") (62 . 94) (370 . 13) (100 . "AcDbPolyline") (90 . 2) (70 . 0)
(43 . 0.0) (10 14193.0614253394 3691.553959276) (10 14200.6037330317 3695.3238687783))
((0 . "LWPOLYLINE") (100 . "AcDbEntity") (8 . "PLANTS") (62 . 94) (370 . 13) (100 . "AcDbPolyline") (90 . 3) (70 . 0)
(43 . 0.0) (10 14193.0614253394 486.4253393665) (10 14215.678959276 481.450678733) (10 14223.2281674208 471.3433257919))
((0 . "LWPOLYLINE") (100 . "AcDbEntity") (8 . "PLANTS") (62 . 94) (370 . 13) (100 . "AcDbPolyline") (90 . 2) (70 . 0)
(43 . 0.0) (10 14223.2281674208 350.6787330317) (10 14193.0614253394 350.6787330317))
((0 . "LWPOLYLINE") (100 . "AcDbEntity") (8 . "PLANTS") (62 . 94) (370 . 13) (100 . "AcDbPolyline") (90 . 2) (70 . 0)
(43 . 0.0) (10 14196.8325791855 3748.1150452489) (10 14204.3736425339 3782.0516968326))
((0 . "LWPOLYLINE") (100 . "AcDbEntity") (8 . "PLANTS") (62 . 94) (370 . 13) (100 . "AcDbPolyline") (90 . 2) (70 . 0)
(43 . 0.0) (10 14196.8325791855 972.850678733) (10 14196.8325791855 957.7686651584))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4749537178)
(40 . 0.5982042444) (40 . 1) (40 . 1) (40 . 1) (40 . 1) (10 14196.8325791855 972.850678733 0.0) (10 14238.3555001709
967.1873439813 0.0) (10 14224.4603627789 1025.0237775392 0.0) (10 14257.8554873693 1056.3135557301 0.0) (10
14295.8658140765 1030.5660331363 0.0) (10 14291.1014705882 1006.7873303167 0.0))
((0 . "LWPOLYLINE") (100 . "AcDbEntity") (8 . "PLANTS") (62 . 94) (370 . 13) (100 . "AcDbPolyline") (90 . 2) (70 . 0)
(43 . 0.0) (10 14208.1447963801 953.996040724) (10 14196.8325791855 957.7686651584))
((0 . "LWPOLYLINE") (100 . "AcDbEntity") (8 . "PLANTS") (62 . 94) (370 . 13) (100 . "AcDbPolyline") (90 . 2) (70 . 0)
(43 . 0.0) (10 14200.6037330317 3895.1738687783) (10 14200.6037330317 3910.2559954751))
((0 . "LWPOLYLINE") (100 . "AcDbEntity") (8 . "PLANTS") (62 . 94) (370 . 13) (100 . "AcDbPolyline") (90 . 2) (70 . 0)
(43 . 0.0) (10 14234.5403846154 3951.7349547511) (10 14200.6037330317 3910.2559954751))
((0 . "LWPOLYLINE") (100 . "AcDbEntity") (8 . "PLANTS") (62 . 94) (370 . 13) (100 . "AcDbPolyline") (90 . 2) (70 . 0)
(43 . 0.0) (10 14200.6037330317 3895.1738687783) (10 14249.6225113122 3895.1738687783))
((0 . "LWPOLYLINE") (100 . "AcDbEntity") (8 . "PLANTS") (62 . 94) (370 . 13) (100 . "AcDbPolyline") (90 . 2) (70 . 0)
(43 . 0.0) (10 14200.6037330317 3895.1738687783) (10 14200.6037330317 3883.8616515837))
((0 . "LWPOLYLINE") (100 . "AcDbEntity") (8 . "PLANTS") (62 . 94) (370 . 13) (100 . "AcDbPolyline") (90 . 3) (70 . 0)
(43 . 0.0) (10 14219.4570135747 3846.1538461538) (10 14209.3419683258 3857.4660633484) (10 14200.6037330317
3883.8616515837))
((0 . "LWPOLYLINE") (100 . "AcDbEntity") (8 . "PLANTS") (62 . 94) (370 . 13) (100 . "AcDbPolyline") (90 . 2) (70 . 0)
(43 . 0.0) (10 14200.6037330317 3808.446040724) (10 14204.3736425339 3782.0516968326))
((0 . "LWPOLYLINE") (100 . "AcDbEntity") (8 . "PLANTS") (62 . 94) (370 . 13) (100 . "AcDbPolyline") (90 . 2) (70 . 0)
(43 . 0.0) (10 14219.4570135747 3846.1538461538) (10 14200.6037330317 3808.446040724))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4656795124) (40
. 1) (40 . 1) (40 . 1) (40 . 1) (10 14351.4324660633 3782.0516968327 0.0) (10 14329.0141369072 3787.3261603625 0.0) (10
14280.496247657 3766.135206892 0.0) (10 14229.7136239464 3767.7448847208 0.0) (10 14204.3736425339 3782.0516968326 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14219.4570135747 3846.1538461538 0.0) (10 14253.0223053166 3823.386369834 0.0) (10 14272.2370419254
3860.6023202189 0.0) (10 14302.4136877828 3861.2372171946 0.0))
((0 . "LWPOLYLINE") (100 . "AcDbEntity") (8 . "PLANTS") (62 . 94) (370 . 13) (100 . "AcDbPolyline") (90 . 3) (70 . 0)
(43 . 0.0) (10 14223.2281674208 411.0096153846) (10 14223.2281674208 403.4700226244) (10 14230.7692307692 395.92760181))
((0 . "LWPOLYLINE") (100 . "AcDbEntity") (8 . "PLANTS") (62 . 94) (370 . 13) (100 . "AcDbPolyline") (90 . 3) (70 . 0)
(43 . 0.0) (10 14242.0814479638 297.8874434389) (10 14240.8842760181 316.742081448) (10 14223.2281674208
350.6787330317))
((0 . "LWPOLYLINE") (100 . "AcDbEntity") (8 . "PLANTS") (62 . 94) (370 . 13) (100 . "AcDbPolyline") (90 . 2) (70 . 0)
(43 . 0.0) (10 14223.2281674208 350.6787330317) (10 14226.9980769231 358.2211538462))
((0 . "LWPOLYLINE") (100 . "AcDbEntity") (8 . "PLANTS") (62 . 94) (370 . 13) (100 . "AcDbPolyline") (90 . 2) (70 . 0)
(43 . 0.0) (10 14245.85260181 938.9140271493) (10 14226.9980769231 938.9140271493))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14279.7892533937 316.742081448 0.0) (10 14269.3859708428 332.221049468 0.0) (10 14252.408753506
363.5778102485 0.0) (10 14226.9980769231 358.2211538462 0.0))
((0 . "LWPOLYLINE") (100 . "AcDbEntity") (8 . "PLANTS") (62 . 94) (370 . 13) (100 . "AcDbPolyline") (90 . 2) (70 . 0)
(43 . 0.0) (10 14230.7692307692 395.92760181) (10 14226.9980769231 358.2211538462))
((0 . "LWPOLYLINE") (100 . "AcDbEntity") (8 . "PLANTS") (62 . 94) (370 . 13) (100 . "AcDbPolyline") (90 . 2) (70 . 0)
(43 . 0.0) (10 14230.7692307692 3966.817081448) (10 14234.5403846154 3951.7349547511))
((0 . "LWPOLYLINE") (100 . "AcDbEntity") (8 . "PLANTS") (62 . 94) (370 . 13) (100 . "AcDbPolyline") (90 . 2) (70 . 0)
(43 . 0.0) (10 14230.7692307692 395.92760181) (10 14249.6225113122 399.69739819))
((0 . "LWPOLYLINE") (100 . "AcDbEntity") (8 . "PLANTS") (62 . 94) (370 . 13) (100 . "AcDbPolyline") (90 . 2) (70 . 0)
(43 . 0.0) (10 14242.0814479638 297.8874434389) (10 14230.7692307692 275.2630090498))
((0 . "LWPOLYLINE") (100 . "AcDbEntity") (8 . "PLANTS") (62 . 94) (370 . 13) (100 . "AcDbPolyline") (90 . 3) (70 . 0)
(43 . 0.0) (10 14257.1648190045 3910.2559954751) (10 14252.189479638 3947.8091628959) (10 14234.5403846154
3951.7349547511))
((0 . "LWPOLYLINE") (100 . "AcDbEntity") (8 . "PLANTS") (62 . 94) (370 . 13) (100 . "AcDbPolyline") (90 . 2) (70 . 0)
(43 . 0.0) (10 14242.0814479638 297.8874434389) (10 14268.4770361991 294.1176470588))
((0 . "LWPOLYLINE") (100 . "AcDbEntity") (8 . "PLANTS") (62 . 94) (370 . 13) (100 . "AcDbPolyline") (90 . 2) (70 . 0)
(43 . 0.0) (10 14249.6225113122 3895.1738687783) (10 14245.85260181 3883.8616515837))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14245.85260181 938.9140271493 0.0) (10 14235.7936443227 954.1331538163 0.0) (10 14258.2388803477
988.5524882849 0.0) (10 14272.2469457014 965.3082579185 0.0))
((0 . "LWPOLYLINE") (100 . "AcDbEntity") (8 . "PLANTS") (62 . 94) (370 . 13) (100 . "AcDbPolyline") (90 . 2) (70 . 0)
(43 . 0.0) (10 14272.2469457014 946.4564479638) (10 14245.85260181 938.9140271493))
((0 . "LWPOLYLINE") (100 . "AcDbEntity") (8 . "PLANTS") (62 . 94) (370 . 13) (100 . "AcDbPolyline") (90 . 2) (70 . 0)
(43 . 0.0) (10 14249.6225113122 3895.1738687783) (10 14257.1648190045 3910.2559954751))
((0 . "LWPOLYLINE") (100 . "AcDbEntity") (8 . "PLANTS") (62 . 94) (370 . 13) (100 . "AcDbPolyline") (90 . 2) (70 . 0)
(43 . 0.0) (10 14272.2469457014 395.92760181) (10 14249.6225113122 399.69739819))
((0 . "LWPOLYLINE") (100 . "AcDbEntity") (8 . "PLANTS") (62 . 94) (370 . 13) (100 . "AcDbPolyline") (90 . 3) (70 . 0)
(43 . 0.0) (10 14260.9347285068 452.4886877828) (10 14249.7771493213 426.0944570136) (10 14249.6225113122 399.69739819))
((0 . "LWPOLYLINE") (100 . "AcDbEntity") (8 . "PLANTS") (62 . 94) (370 . 13) (100 . "AcDbPolyline") (90 . 2) (70 . 0)
(43 . 0.0) (10 14285.445361991 3912.1421945701) (10 14257.1648190045 3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14260.9347285068 241.3263574661 0.0) (10 14277.9552573429 224.5744302917 0.0) (10 14308.8240372675
229.6844812788 0.0) (10 14325.0381221719 245.0989819005 0.0))
((0 . "LWPOLYLINE") (100 . "AcDbEntity") (8 . "PLANTS") (62 . 94) (370 . 13) (100 . "AcDbPolyline") (90 . 2) (70 . 0)
(43 . 0.0) (10 14260.9347285068 241.3263574661) (10 14268.4770361991 275.2630090498))
((0 . "LWPOLYLINE") (100 . "AcDbEntity") (8 . "PLANTS") (62 . 94) (370 . 13) (100 . "AcDbPolyline") (90 . 2) (70 . 0)
(43 . 0.0) (10 14264.7058823529 3989.4415158371) (10 14276.0180995475 3974.3593891403))
((0 . "LWPOLYLINE") (100 . "AcDbEntity") (8 . "PLANTS") (62 . 94) (370 . 13) (100 . "AcDbPolyline") (90 . 2) (70 . 0)
(43 . 0.0) (10 14268.4770361991 294.1176470588) (10 14268.4770361991 275.2630090498))
((0 . "LWPOLYLINE") (100 . "AcDbEntity") (8 . "PLANTS") (62 . 94) (370 . 13) (100 . "AcDbPolyline") (90 . 2) (70 . 0)
(43 . 0.0) (10 14279.7892533937 316.742081448) (10 14268.4770361991 294.1176470588))
((0 . "LWPOLYLINE") (100 . "AcDbEntity") (8 . "PLANTS") (62 . 94) (370 . 13) (100 . "AcDbPolyline") (90 . 2) (70 . 0)
(43 . 0.0) (10 14302.4136877828 275.2630090498) (10 14268.4770361991 275.2630090498))
((0 . "LWPOLYLINE") (100 . "AcDbEntity") (8 . "PLANTS") (62 . 94) (370 . 13) (100 . "AcDbPolyline") (90 . 2) (70 . 0)
(43 . 0.0) (10 14302.4136877828 965.3082579186) (10 14272.2469457014 965.3082579186))
((0 . "LWPOLYLINE") (100 . "AcDbEntity") (8 . "PLANTS") (62 . 94) (370 . 13) (100 . "AcDbPolyline") (90 . 2) (70 . 0)
(43 . 0.0) (10 14272.2469457014 946.4564479638) (10 14272.2469457014 965.3082579186))
((0 . "LWPOLYLINE") (100 . "AcDbEntity") (8 . "PLANTS") (62 . 94) (370 . 13) (100 . "AcDbPolyline") (90 . 2) (70 . 0)
(43 . 0.0) (10 14272.2469457014 946.4564479638) (10 14291.1014705882 927.6018099548))
((0 . "LWPOLYLINE") (100 . "AcDbEntity") (8 . "PLANTS") (62 . 94) (370 . 13) (100 . "AcDbPolyline") (90 . 2) (70 . 0)
(43 . 0.0) (10 14283.5591628959 373.3031674208) (10 14272.2469457014 395.92760181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14325.038122172 358.2211538461 0.0) (10 14363.8727271981 390.0147254391 0.0) (10 14293.1779384254
415.2117087085 0.0) (10 14272.2469457014 395.9276018099 0.0))
((0 . "LWPOLYLINE") (100 . "AcDbEntity") (8 . "PLANTS") (62 . 94) (370 . 13) (100 . "AcDbPolyline") (90 . 3) (70 . 0)
(43 . 0.0) (10 14371.3207427636 516.5890582527) (10 14291.1014705882 516.5852941176) (10 14279.7892533937
512.8195701357))
((0 . "LWPOLYLINE") (100 . "AcDbEntity") (8 . "PLANTS") (62 . 94) (370 . 13) (100 . "AcDbPolyline") (90 . 2) (70 . 0)
(43 . 0.0) (10 14279.7892533937 316.742081448) (10 14304.2986425339 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14302.4136877828 3861.2372171946 0.0) (10 14287.2576799433 3875.9738824421 0.0) (10 14302.9594869132
3899.0983970523 0.0) (10 14285.445361991 3912.1421945701 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14374.0569004525 3966.8170814479 0.0) (10 14338.4667241567 3975.8747995981 0.0) (10 14273.2702195741
3961.512762083 0.0) (10 14285.4453619909 3912.14219457 0.0))
((0 . "LWPOLYLINE") (100 . "AcDbEntity") (8 . "PLANTS") (62 . 94) (370 . 13) (100 . "AcDbPolyline") (90 . 2) (70 . 0)
(43 . 0.0) (10 14285.445361991 3912.1421945701) (10 14309.9547511312 3914.0271493213))
((0 . "LWPOLYLINE") (100 . "AcDbEntity") (8 . "PLANTS") (62 . 94) (370 . 13) (100 . "AcDbPolyline") (90 . 3) (70 . 0)
(43 . 0.0) (10 14298.6425339367 1070.8908371041) (10 14294.8713800905 1070.8908371041) (10 14291.1014705882
1063.3484162896))
((0 . "LWPOLYLINE") (100 . "AcDbEntity") (8 . "PLANTS") (62 . 94) (370 . 13) (100 . "AcDbPolyline") (90 . 2) (70 . 0)
(43 . 0.0) (10 14294.8713800905 904.9773755656) (10 14291.1014705882 927.6018099548))
((0 . "LWPOLYLINE") (100 . "AcDbEntity") (8 . "PLANTS") (62 . 94) (370 . 13) (100 . "AcDbPolyline") (90 . 3) (70 . 0)
(43 . 0.0) (10 14302.4136877828 965.3082579186) (10 14301.3573529412 942.6838235294) (10 14291.1014705882
927.6018099548))
((0 . "LWPOLYLINE") (100 . "AcDbEntity") (8 . "PLANTS") (62 . 94) (370 . 13) (100 . "AcDbPolyline") (90 . 2) (70 . 0)
(43 . 0.0) (10 14336.3503393665 904.9773755656) (10 14294.8713800905 904.9773755656))
((0 . "LWPOLYLINE") (100 . "AcDbEntity") (8 . "PLANTS") (62 . 94) (370 . 13) (100 . "AcDbPolyline") (90 . 3) (70 . 0)
(43 . 0.0) (10 14298.6425339367 1070.8908371041) (10 14336.3503393665 1058.5214932127) (10 14351.4324660633
1040.7239819005))
((0 . "LWPOLYLINE") (100 . "AcDbEntity") (8 . "PLANTS") (62 . 94) (370 . 13) (100 . "AcDbPolyline") (90 . 2) (70 . 0)
(43 . 0.0) (10 14298.6425339367 1070.8908371041) (10 14302.4136877828 1078.4304298643))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3528235978) (40
. 1) (40 . 1) (40 . 1) (40 . 1) (10 14302.4136877828 3861.2372171947 0.0) (10 14316.2881899004 3861.6643138606 0.0) (10
14343.1823462699 3833.5961328869 0.0) (10 14385.2242591943 3833.1169220694 0.0) (10 14404.2236425339 3815.9883484163
0.0))
((0 . "LWPOLYLINE") (100 . "AcDbEntity") (8 . "PLANTS") (62 . 94) (370 . 13) (100 . "AcDbPolyline") (90 . 2) (70 . 0)
(43 . 0.0) (10 14321.2669683258 969.0808823529) (10 14302.4136877828 965.3082579186))
((0 . "LWPOLYLINE") (100 . "AcDbEntity") (8 . "PLANTS") (62 . 94) (370 . 13) (100 . "AcDbPolyline") (90 . 2) (70 . 0)
(43 . 0.0) (10 14302.4136877828 275.2630090498) (10 14325.0381221719 260.1809954751))
((0 . "LWPOLYLINE") (100 . "AcDbEntity") (8 . "PLANTS") (62 . 94) (370 . 13) (100 . "AcDbPolyline") (90 . 2) (70 . 0)
(43 . 0.0) (10 14302.4136877828 275.2630090498) (10 14304.2986425339 316.742081448))
((0 . "LWPOLYLINE") (100 . "AcDbEntity") (8 . "PLANTS") (62 . 94) (370 . 13) (100 . "AcDbPolyline") (90 . 2) (70 . 0)
(43 . 0.0) (10 14340.1202488688 316.742081448) (10 14304.2986425339 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14325.0381221719 358.2211538462 0.0) (10 14305.6642027988 360.6406760344 0.0) (10 14303.6474682733
325.4727566434 0.0) (10 14304.2986425339 316.742081448 0.0))
((0 . "LWPOLYLINE") (100 . "AcDbEntity") (8 . "PLANTS") (62 . 94) (370 . 13) (100 . "AcDbPolyline") (90 . 3) (70 . 0)
(43 . 0.0) (10 14336.3503393665 1018.0995475113) (10 14321.4147058824 1022.9264705882) (10 14313.7259049774
1033.181561086))
((0 . "LWPOLYLINE") (100 . "AcDbEntity") (8 . "PLANTS") (62 . 94) (370 . 13) (100 . "AcDbPolyline") (90 . 2) (70 . 0)
(43 . 0.0) (10 14321.2669683258 969.0808823529) (10 14321.2669683258 980.3930995475))
((0 . "LWPOLYLINE") (100 . "AcDbEntity") (8 . "PLANTS") (62 . 94) (370 . 13) (100 . "AcDbPolyline") (90 . 3) (70 . 0)
(43 . 0.0) (10 14321.2669683258 969.0808823529) (10 14336.3503393665 970.1365384615) (10 14347.6625565611
976.6204751131))
((0 . "LWPOLYLINE") (100 . "AcDbEntity") (8 . "PLANTS") (62 . 94) (370 . 13) (100 . "AcDbPolyline") (90 . 3) (70 . 0)
(43 . 0.0) (10 14340.1202488688 316.742081448) (10 14338.9160633484 346.760520362) (10 14325.0381221719 358.2211538462))
((0 . "LWPOLYLINE") (100 . "AcDbEntity") (8 . "PLANTS") (62 . 94) (370 . 13) (100 . "AcDbPolyline") (90 . 2) (70 . 0)
(43 . 0.0) (10 14325.0381221719 245.0989819005) (10 14325.0381221719 260.1809954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14347.6625565611 305.4298642534 0.0) (10 14332.6255655682 292.5930129589 0.0) (10 14348.9772525869
267.9148723868 0.0) (10 14325.0381221719 260.1809954751 0.0))
((0 . "LWPOLYLINE") (100 . "AcDbEntity") (8 . "PLANTS") (62 . 94) (370 . 13) (100 . "AcDbPolyline") (90 . 2) (70 . 0)
(43 . 0.0) (10 14362.7446832579 245.0989819005) (10 14325.0381221719 245.0989819005))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14336.3503393665 904.9773755656 0.0) (10 14376.8418921727 889.8940655387 0.0) (10 14425.6219902873
889.656884425 0.0) (10 14464.554638009 908.7471719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14336.3503393665 904.9773755656 0.0) (10 14338.8696694972 937.6475125746 0.0) (10 14382.13457267
937.4045626762 0.0) (10 14385.3691176471 969.0808823529 0.0))
((0 . "LWPOLYLINE") (100 . "AcDbEntity") (8 . "PLANTS") (62 . 94) (370 . 13) (100 . "AcDbPolyline") (90 . 2) (70 . 0)
(43 . 0.0) (10 14340.1202488688 316.742081448) (10 14347.6625565611 305.4298642534))
((0 . "LWPOLYLINE") (100 . "AcDbEntity") (8 . "PLANTS") (62 . 94) (370 . 13) (100 . "AcDbPolyline") (90 . 3) (70 . 0)
(43 . 0.0) (10 14366.5158371041 1078.4304298643) (10 14348.859841629 1101.0548642534) (10 14343.8914027149
1127.4519230769))
((0 . "LWPOLYLINE") (100 . "AcDbEntity") (8 . "PLANTS") (62 . 94) (370 . 13) (100 . "AcDbPolyline") (90 . 3) (70 . 0)
(43 . 0.0) (10 14381.5992081448 286.5752262443) (10 14370.2869909502 296.6902714932) (10 14347.6625565611
305.4298642534))
((0 . "LWPOLYLINE") (100 . "AcDbEntity") (8 . "PLANTS") (62 . 94) (370 . 13) (100 . "AcDbPolyline") (90 . 2) (70 . 0)
(43 . 0.0) (10 14351.4324660633 3774.5093891403) (10 14351.4324660633 3782.0516968326))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14351.4324660633 3782.0516968326 0.0) (10 14366.5263780292 3802.369658917 0.0) (10 14401.5836371185
3780.3267912471 0.0) (10 14404.2236425339 3815.9883484163 0.0))
((0 . "LWPOLYLINE") (100 . "AcDbEntity") (8 . "PLANTS") (62 . 94) (370 . 13) (100 . "AcDbPolyline") (90 . 3) (70 . 0)
(43 . 0.0) (10 14351.4324660633 3774.5093891403) (10 14377.8280542986 3751.8787330317) (10 14392.9114253394
3733.0316742081))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14294.0030751495 3643.1527679713 0.0) (10 14263.1226250709 3637.3327427059 0.0) (10 14293.4353251156
3687.8380650036 0.0) (10 14298.4895004182 3693.8838844717 0.0))
((0 . "LWPOLYLINE") (100 . "AcDbEntity") (8 . "PLANTS") (62 . 94) (370 . 13) (100 . "AcDbPolyline") (90 . 3) (70 . 0)
(43 . 0.0) (10 14318.6388702633 3733.0316742081) (10 14341.1765837104 3766.9621040724) (10 14351.4324660633
3774.5093891403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14415.5358597285 3865.0071266968 0.0) (10 14387.5372364804 3863.6362259355 0.0) (10 14368.344246911
3894.1346168959 0.0) (10 14355.2036199095 3914.0271493213 0.0))
((0 . "LWPOLYLINE") (100 . "AcDbEntity") (8 . "PLANTS") (62 . 94) (370 . 13) (100 . "AcDbPolyline") (90 . 3) (70 . 0)
(43 . 0.0) (10 14362.7446832579 245.0989819005) (10 14377.8280542986 233.7858597285) (10 14430.6179864253
233.7858597285))
((0 . "LWPOLYLINE") (100 . "AcDbEntity") (8 . "PLANTS") (62 . 94) (370 . 13) (100 . "AcDbPolyline") (90 . 3) (70 . 0)
(43 . 0.0) (10 14362.7446832579 245.0989819005) (10 14376.6238687783 263.9507918552) (10 14381.5992081448
286.5752262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14366.5158371041 1010.5571266968 0.0) (10 14364.6909486601 992.8547267511 0.0) (10 14393.5841836007
989.097794491 0.0) (10 14385.3691176471 969.0808823529 0.0))
((0 . "LWPOLYLINE") (100 . "AcDbEntity") (8 . "PLANTS") (62 . 94) (370 . 13) (100 . "AcDbPolyline") (90 . 2) (70 . 0)
(43 . 0.0) (10 14374.0569004525 3966.817081448) (10 14370.2869909502 3955.5048642534))
((0 . "LWPOLYLINE") (100 . "AcDbEntity") (8 . "PLANTS") (62 . 94) (370 . 13) (100 . "AcDbPolyline") (90 . 2) (70 . 0)
(43 . 0.0) (10 14374.0569004525 3966.817081448) (10 14381.5992081448 3966.817081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14381.5992081448 3966.817081448 0.0) (10 14403.8865336754 3975.7436668996 0.0) (10 14403.1865029686
3943.040835667 0.0) (10 14423.0769230769 3944.1926470588 0.0))
((0 . "LWPOLYLINE") (100 . "AcDbEntity") (8 . "PLANTS") (62 . 94) (370 . 13) (100 . "AcDbPolyline") (90 . 3) (70 . 0)
(43 . 0.0) (10 14381.5992081448 3966.817081448) (10 14382.7964932127 3981.8942307692) (10 14389.1402714932
3989.4415158371))
((0 . "LWPOLYLINE") (100 . "AcDbEntity") (8 . "PLANTS") (62 . 94) (370 . 13) (100 . "AcDbPolyline") (90 . 3) (70 . 0)
(43 . 0.0) (10 14381.5992081448 286.5752262443) (10 14404.2236425339 304.3735294118) (10 14419.3057692308
309.1996606335))
((0 . "LWPOLYLINE") (100 . "AcDbEntity") (8 . "PLANTS") (62 . 94) (370 . 13) (100 . "AcDbPolyline") (90 . 3) (70 . 0)
(43 . 0.0) (10 14385.3691176471 969.0808823529) (10 14407.9935520362 961.686199095) (10 14426.8480769231
961.5384615385))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.3197581914)
(40 . 0.4858830924) (40 . 0.9016487215) (40 . 1) (40 . 1) (40 . 1) (40 . 1) (10 14449.4725113122 414.782239819 0.0) (10
14433.8773759294 409.7531901167 0.0) (10 14402.1801980132 436.6672445471 0.0) (10 14375.4848527166 399.8764317225 0.0)
(10 14361.3654332602 352.4108206506 0.0) (10 14378.7898993792 338.4867871726 0.0) (10 14385.369117647 343.1363122171
0.0))
((0 . "LWPOLYLINE") (100 . "AcDbEntity") (8 . "PLANTS") (62 . 94) (370 . 13) (100 . "AcDbPolyline") (90 . 2) (70 . 0)
(43 . 0.0) (10 14392.9114253394 3733.0316742081) (10 14415.5358597285 3733.0316742081))
((0 . "LWPOLYLINE") (100 . "AcDbEntity") (8 . "PLANTS") (62 . 94) (370 . 13) (100 . "AcDbPolyline") (90 . 3) (70 . 0)
(43 . 0.0) (10 14453.2424208145 343.1363122172) (10 14434.382239819 365.5998868778) (10 14400.4524886878
350.6787330317))
((0 . "LWPOLYLINE") (100 . "AcDbEntity") (8 . "PLANTS") (62 . 94) (370 . 13) (100 . "AcDbPolyline") (90 . 3) (70 . 0)
(43 . 0.0) (10 14434.3891402715 3819.7582579186) (10 14426.8411764706 3816.136199095) (10 14404.2236425339
3815.9883484163))
((0 . "LWPOLYLINE") (100 . "AcDbEntity") (8 . "PLANTS") (62 . 94) (370 . 13) (100 . "AcDbPolyline") (90 . 3) (70 . 0)
(43 . 0.0) (10 14434.3891402715 3831.0704751131) (10 14424.1332579186 3842.3833710407) (10 14415.5358597285
3865.0071266968))
((0 . "LWPOLYLINE") (100 . "AcDbEntity") (8 . "PLANTS") (62 . 94) (370 . 13) (100 . "AcDbPolyline") (90 . 2) (70 . 0)
(43 . 0.0) (10 14430.6179864253 3891.4027149321) (10 14415.5358597285 3865.0071266968))
((0 . "LWPOLYLINE") (100 . "AcDbEntity") (8 . "PLANTS") (62 . 94) (370 . 13) (100 . "AcDbPolyline") (90 . 3) (70 . 0)
(43 . 0.0) (10 14441.9302036199 3751.8849547511) (10 14430.6179864253 3750.6811085973) (10 14415.5358597285
3733.0316742081))
((0 . "LWPOLYLINE") (100 . "AcDbEntity") (8 . "PLANTS") (62 . 94) (370 . 13) (100 . "AcDbPolyline") (90 . 3) (70 . 0)
(43 . 0.0) (10 14430.6179864253 233.7858597285) (10 14434.2345022624 271.4932126697) (10 14419.3057692308
309.1996606335))
((0 . "LWPOLYLINE") (100 . "AcDbEntity") (8 . "PLANTS") (62 . 94) (370 . 13) (100 . "AcDbPolyline") (90 . 3) (70 . 0)
(43 . 0.0) (10 14453.2424208145 328.0542986425) (10 14426.8549773756 319.4562217195) (10 14419.3057692308
309.1996606335))
((0 . "LWPOLYLINE") (100 . "AcDbEntity") (8 . "PLANTS") (62 . 94) (370 . 13) (100 . "AcDbPolyline") (90 . 3) (70 . 0)
(43 . 0.0) (10 14430.6179864253 3891.4027149321) (10 14423.2246606335 3910.2559954751) (10 14423.0769230769
3944.1926470588))
((0 . "LWPOLYLINE") (100 . "AcDbEntity") (8 . "PLANTS") (62 . 94) (370 . 13) (100 . "AcDbPolyline") (90 . 2) (70 . 0)
(43 . 0.0) (10 14423.0769230769 3944.1926470588) (10 14445.7013574661 3959.2760180995))
((0 . "LWPOLYLINE") (100 . "AcDbEntity") (8 . "PLANTS") (62 . 94) (370 . 13) (100 . "AcDbPolyline") (90 . 2) (70 . 0)
(43 . 0.0) (10 14464.554638009 908.7471719457) (10 14426.8480769231 961.5384615385))
((0 . "LWPOLYLINE") (100 . "AcDbEntity") (8 . "PLANTS") (62 . 94) (370 . 13) (100 . "AcDbPolyline") (90 . 2) (70 . 0)
(43 . 0.0) (10 14438.1602941176 980.3930995475) (10 14426.8480769231 961.5384615385))
((0 . "LWPOLYLINE") (100 . "AcDbEntity") (8 . "PLANTS") (62 . 94) (370 . 13) (100 . "AcDbPolyline") (90 . 2) (70 . 0)
(43 . 0.0) (10 14430.6179864253 3891.4027149321) (10 14460.7847285068 3887.631561086))
((0 . "LWPOLYLINE") (100 . "AcDbEntity") (8 . "PLANTS") (62 . 94) (370 . 13) (100 . "AcDbPolyline") (90 . 2) (70 . 0)
(43 . 0.0) (10 14430.6179864253 1074.6606334842) (10 14438.1602941176 1070.8908371041))
((0 . "LWPOLYLINE") (100 . "AcDbEntity") (8 . "PLANTS") (62 . 94) (370 . 13) (100 . "AcDbPolyline") (90 . 3) (70 . 0)
(43 . 0.0) (10 14483.4091628959 241.3263574661) (10 14457.0135746606 233.7858597285) (10 14430.6179864253
233.7858597285))
((0 . "LWPOLYLINE") (100 . "AcDbEntity") (8 . "PLANTS") (62 . 94) (370 . 13) (100 . "AcDbPolyline") (90 . 2) (70 . 0)
(43 . 0.0) (10 14434.3891402715 3819.7582579186) (10 14434.3891402715 3831.0704751131))
((0 . "LWPOLYLINE") (100 . "AcDbEntity") (8 . "PLANTS") (62 . 94) (370 . 13) (100 . "AcDbPolyline") (90 . 2) (70 . 0)
(43 . 0.0) (10 14434.3891402715 3831.0704751131) (10 14460.7847285068 3857.4660633484))
((0 . "LWPOLYLINE") (100 . "AcDbEntity") (8 . "PLANTS") (62 . 94) (370 . 13) (100 . "AcDbPolyline") (90 . 2) (70 . 0)
(43 . 0.0) (10 14434.3891402715 3819.7582579186) (10 14445.7013574661 3800.9049773756))
((0 . "LWPOLYLINE") (100 . "AcDbEntity") (8 . "PLANTS") (62 . 94) (370 . 13) (100 . "AcDbPolyline") (90 . 2) (70 . 0)
(43 . 0.0) (10 14438.1602941176 1123.6792986425) (10 14434.3891402715 1108.5972850679))
((0 . "LWPOLYLINE") (100 . "AcDbEntity") (8 . "PLANTS") (62 . 94) (370 . 13) (100 . "AcDbPolyline") (90 . 2) (70 . 0)
(43 . 0.0) (10 14438.1602941176 1070.8908371041) (10 14441.9302036199 1044.4937782805))
((0 . "LWPOLYLINE") (100 . "AcDbEntity") (8 . "PLANTS") (62 . 94) (370 . 13) (100 . "AcDbPolyline") (90 . 3) (70 . 0)
(43 . 0.0) (10 14438.1602941176 1070.8908371041) (10 14453.2424208145 1081.0044117647) (10 14472.0969457014
1085.9728506787))
((0 . "LWPOLYLINE") (100 . "AcDbEntity") (8 . "PLANTS") (62 . 94) (370 . 13) (100 . "AcDbPolyline") (90 . 2) (70 . 0)
(43 . 0.0) (10 14438.1602941176 980.3930995475) (10 14445.7013574661 980.3930995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14438.1602941177 980.3930995475 0.0) (10 14413.5335036179 996.2729451749 0.0) (10 14410.1167060354
1034.9472323479 0.0) (10 14441.9302036199 1044.4937782805 0.0))
((0 . "LWPOLYLINE") (100 . "AcDbEntity") (8 . "PLANTS") (62 . 94) (370 . 13) (100 . "AcDbPolyline") (90 . 3) (70 . 0)
(43 . 0.0) (10 14441.9302036199 3751.8849547511) (10 14498.4912895928 3733.1797511312) (10 14524.8868778281
3733.0316742081))
((0 . "LWPOLYLINE") (100 . "AcDbEntity") (8 . "PLANTS") (62 . 94) (370 . 13) (100 . "AcDbPolyline") (90 . 3) (70 . 0)
(43 . 0.0) (10 14441.9302036199 3751.8849547511) (10 14442.0779411765 3793.3570135747) (10 14445.7013574661
3800.9049773756))
((0 . "LWPOLYLINE") (100 . "AcDbEntity") (8 . "PLANTS") (62 . 94) (370 . 13) (100 . "AcDbPolyline") (90 . 3) (70 . 0)
(43 . 0.0) (10 14475.8668552036 1021.8693438914) (10 14453.2424208145 1043.2903846154) (10 14441.9302036199
1044.4937782805))
((0 . "LWPOLYLINE") (100 . "AcDbEntity") (8 . "PLANTS") (62 . 94) (370 . 13) (100 . "AcDbPolyline") (90 . 3) (70 . 0)
(43 . 0.0) (10 14468.3257918552 3914.0271493213) (10 14457.9083710407 3944.1926470588) (10 14445.7013574661
3959.2760180995))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14468.3257918552 4012.0659502262 0.0) (10 14471.2806171284 3990.9377491294 0.0) (10 14446.3283740524
3979.9924367157 0.0) (10 14445.7013574661 3959.2760180995 0.0))
((0 . "LWPOLYLINE") (100 . "AcDbEntity") (8 . "PLANTS") (62 . 94) (370 . 13) (100 . "AcDbPolyline") (90 . 3) (70 . 0)
(43 . 0.0) (10 14445.7013574661 3800.9049773756) (10 14479.6380090498 3800.7569004525) (10 14513.5746606335
3793.3639140271))
((0 . "LWPOLYLINE") (100 . "AcDbEntity") (8 . "PLANTS") (62 . 94) (370 . 13) (100 . "AcDbPolyline") (90 . 3) (70 . 0)
(43 . 0.0) (10 14445.7013574661 980.3930995475) (10 14464.4067873303 965.3033936652) (10 14487.1790723982
935.1442307692))
((0 . "LWPOLYLINE") (100 . "AcDbEntity") (8 . "PLANTS") (62 . 94) (370 . 13) (100 . "AcDbPolyline") (90 . 2) (70 . 0)
(43 . 0.0) (10 14475.8668552036 1021.8693438914) (10 14445.7013574661 980.3930995475))
((0 . "LWPOLYLINE") (100 . "AcDbEntity") (8 . "PLANTS") (62 . 94) (370 . 13) (100 . "AcDbPolyline") (90 . 2) (70 . 0)
(43 . 0.0) (10 14449.4725113122 444.9462669683) (10 14449.4725113122 414.782239819))
((0 . "LWPOLYLINE") (100 . "AcDbEntity") (8 . "PLANTS") (62 . 94) (370 . 13) (100 . "AcDbPolyline") (90 . 3) (70 . 0)
(43 . 0.0) (10 14449.4725113122 414.782239819) (10 14468.3257918552 399.69739819) (10 14490.9502262443 373.3031674208))
((0 . "LWPOLYLINE") (100 . "AcDbEntity") (8 . "PLANTS") (62 . 94) (370 . 13) (100 . "AcDbPolyline") (90 . 2) (70 . 0)
(43 . 0.0) (10 14453.2424208145 343.1363122172) (10 14453.2424208145 328.0542986425))
((0 . "LWPOLYLINE") (100 . "AcDbEntity") (8 . "PLANTS") (62 . 94) (370 . 13) (100 . "AcDbPolyline") (90 . 3) (70 . 0)
(43 . 0.0) (10 14490.9502262443 358.2211538462) (10 14468.3257918552 353.2451357466) (10 14453.2424208145
343.1363122172))
((0 . "LWPOLYLINE") (100 . "AcDbEntity") (8 . "PLANTS") (62 . 94) (370 . 13) (100 . "AcDbPolyline") (90 . 3) (70 . 0)
(43 . 0.0) (10 14453.2424208145 328.0542986425) (10 14463.4981900452 320.5070135747) (10 14468.3257918552
301.6600678733))
((0 . "LWPOLYLINE") (100 . "AcDbEntity") (8 . "PLANTS") (62 . 94) (370 . 13) (100 . "AcDbPolyline") (90 . 2) (70 . 0)
(43 . 0.0) (10 14460.7847285068 3887.631561086) (10 14460.7847285068 3857.4660633484))
((0 . "LWPOLYLINE") (100 . "AcDbEntity") (8 . "PLANTS") (62 . 94) (370 . 13) (100 . "AcDbPolyline") (90 . 2) (70 . 0)
(43 . 0.0) (10 14468.3257918552 3906.4860859729) (10 14460.7847285068 3887.631561086))
((0 . "LWPOLYLINE") (100 . "AcDbEntity") (8 . "PLANTS") (62 . 94) (370 . 13) (100 . "AcDbPolyline") (90 . 2) (70 . 0)
(43 . 0.0) (10 14490.9502262443 3853.6949095023) (10 14460.7847285068 3857.4660633484))
((0 . "LWPOLYLINE") (100 . "AcDbEntity") (8 . "PLANTS") (62 . 94) (370 . 13) (100 . "AcDbPolyline") (90 . 2) (70 . 0)
(43 . 0.0) (10 14464.554638009 908.7471719457) (10 14483.4091628959 908.7471719457))
((0 . "LWPOLYLINE") (100 . "AcDbEntity") (8 . "PLANTS") (62 . 94) (370 . 13) (100 . "AcDbPolyline") (90 . 2) (70 . 0)
(43 . 0.0) (10 14468.3257918552 3914.0271493213) (10 14475.8668552036 3914.0271493213))
((0 . "LWPOLYLINE") (100 . "AcDbEntity") (8 . "PLANTS") (62 . 94) (370 . 13) (100 . "AcDbPolyline") (90 . 2) (70 . 0)
(43 . 0.0) (10 14468.3257918552 3914.0271493213) (10 14468.3257918552 3906.4860859729))
((0 . "LWPOLYLINE") (100 . "AcDbEntity") (8 . "PLANTS") (62 . 94) (370 . 13) (100 . "AcDbPolyline") (90 . 3) (70 . 0)
(43 . 0.0) (10 14468.3257918552 3906.4860859729) (10 14472.0969457014 3906.4860859729) (10 14475.8668552036
3914.0271493213))
((0 . "LWPOLYLINE") (100 . "AcDbEntity") (8 . "PLANTS") (62 . 94) (370 . 13) (100 . "AcDbPolyline") (90 . 2) (70 . 0)
(43 . 0.0) (10 14506.0335972851 294.1176470588) (10 14468.3257918552 301.6600678733))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5607460946) (40
. 1) (40 . 1) (40 . 1) (40 . 1) (10 14483.4091628959 252.6385746606 0.0) (10 14472.7911798182 256.8934578251 0.0) (10
14470.2003222759 276.701106378 0.0) (10 14464.5554864293 294.3943448594 0.0) (10 14468.3257918552 301.6600678733 0.0))
((0 . "LWPOLYLINE") (100 . "AcDbEntity") (8 . "PLANTS") (62 . 94) (370 . 13) (100 . "AcDbPolyline") (90 . 2) (70 . 0)
(43 . 0.0) (10 14506.0335972851 3925.3393665158) (10 14475.8668552036 3914.0271493213))
((0 . "LWPOLYLINE") (100 . "AcDbEntity") (8 . "PLANTS") (62 . 94) (370 . 13) (100 . "AcDbPolyline") (90 . 2) (70 . 0)
(43 . 0.0) (10 14475.8668552036 1021.8693438914) (10 14500.3774886878 1019.9858597285))
((0 . "LWPOLYLINE") (100 . "AcDbEntity") (8 . "PLANTS") (62 . 94) (370 . 13) (100 . "AcDbPolyline") (90 . 3) (70 . 0)
(43 . 0.0) (10 14528.6580316742 901.2075791855) (10 14494.7213800905 901.3608597285) (10 14483.4091628959
908.7471719457))
((0 . "LWPOLYLINE") (100 . "AcDbEntity") (8 . "PLANTS") (62 . 94) (370 . 13) (100 . "AcDbPolyline") (90 . 2) (70 . 0)
(43 . 0.0) (10 14483.4091628959 908.7471719457) (10 14487.1790723982 935.1442307692))
((0 . "LWPOLYLINE") (100 . "AcDbEntity") (8 . "PLANTS") (62 . 94) (370 . 13) (100 . "AcDbPolyline") (90 . 2) (70 . 0)
(43 . 0.0) (10 14483.4091628959 252.6385746606) (10 14483.4091628959 241.3263574661))
((0 . "LWPOLYLINE") (100 . "AcDbEntity") (8 . "PLANTS") (62 . 94) (370 . 13) (100 . "AcDbPolyline") (90 . 2) (70 . 0)
(43 . 0.0) (10 14483.4091628959 252.6385746606) (10 14506.0335972851 275.2630090498))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14483.4091628959 241.3263574661 0.0) (10 14500.4165605961 236.0491182377 0.0) (10 14531.9944251728
222.6037682843 0.0) (10 14543.740158371 245.0989819004 0.0))
((0 . "LWPOLYLINE") (100 . "AcDbEntity") (8 . "PLANTS") (62 . 94) (370 . 13) (100 . "AcDbPolyline") (90 . 2) (70 . 0)
(43 . 0.0) (10 14498.4912895928 938.9140271493) (10 14487.1790723982 935.1442307692))
((0 . "LWPOLYLINE") (100 . "AcDbEntity") (8 . "PLANTS") (62 . 94) (370 . 13) (100 . "AcDbPolyline") (90 . 2) (70 . 0)
(43 . 0.0) (10 14490.9502262443 3853.6949095023) (10 14494.7213800905 3834.8416289593))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14490.9502262443 3853.6949095023 0.0) (10 14496.1776879751 3870.0169237332 0.0) (10 14521.1273065652
3865.6243430362 0.0) (10 14524.8868778281 3883.8616515837 0.0))
((0 . "LWPOLYLINE") (100 . "AcDbEntity") (8 . "PLANTS") (62 . 94) (370 . 13) (100 . "AcDbPolyline") (90 . 2) (70 . 0)
(43 . 0.0) (10 14490.9502262443 358.2211538462) (10 14490.9502262443 373.3031674208))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.384198982)
(40 . 0.6509602967) (40 . 1) (40 . 1) (40 . 1) (40 . 1) (10 14490.9502262444 373.3031674208 0.0) (10 14514.2922263872
376.6267604681 0.0) (10 14497.2479631234 433.2331888556 0.0) (10 14553.7590537437 431.9018702847 0.0) (10
14555.9999620417 385.1944989755 0.0) (10 14539.9702488688 377.0729638009 0.0))
((0 . "LWPOLYLINE") (100 . "AcDbEntity") (8 . "PLANTS") (62 . 94) (370 . 13) (100 . "AcDbPolyline") (90 . 2) (70 . 0)
(43 . 0.0) (10 14490.9502262443 358.2211538462) (10 14509.8035067873 350.6787330317))
((0 . "LWPOLYLINE") (100 . "AcDbEntity") (8 . "PLANTS") (62 . 94) (370 . 13) (100 . "AcDbPolyline") (90 . 3) (70 . 0)
(43 . 0.0) (10 14526.7718325792 937.0277149321) (10 14506.0404977376 935.2912895928) (10 14498.4912895928
938.9140271493))
((0 . "LWPOLYLINE") (100 . "AcDbEntity") (8 . "PLANTS") (62 . 94) (370 . 13) (100 . "AcDbPolyline") (90 . 2) (70 . 0)
(43 . 0.0) (10 14498.4912895928 938.9140271493) (10 14509.8035067873 980.3930995475))
((0 . "LWPOLYLINE") (100 . "AcDbEntity") (8 . "PLANTS") (62 . 94) (370 . 13) (100 . "AcDbPolyline") (90 . 3) (70 . 0)
(43 . 0.0) (10 14506.0335972851 456.2584841629) (10 14507.5498868778 463.8078054299) (10 14506.6874403192
465.2430695247))
((0 . "LWPOLYLINE") (100 . "AcDbEntity") (8 . "PLANTS") (62 . 94) (370 . 13) (100 . "AcDbPolyline") (90 . 3) (70 . 0)
(43 . 0.0) (10 14500.3774886878 1019.9858597285) (10 14499.5449095023 1006.7908371041) (10 14509.8035067873
980.3930995475))
((0 . "LWPOLYLINE") (100 . "AcDbEntity") (8 . "PLANTS") (62 . 94) (370 . 13) (100 . "AcDbPolyline") (90 . 3) (70 . 0)
(43 . 0.0) (10 14500.3774886878 1019.9858597285) (10 14503.4666289593 1052.036199095) (10 14517.3458144796
1063.3484162896))
((0 . "LWPOLYLINE") (100 . "AcDbEntity") (8 . "PLANTS") (62 . 94) (370 . 13) (100 . "AcDbPolyline") (90 . 2) (70 . 0)
(43 . 0.0) (10 14521.1157239819 1021.8693438914) (10 14500.3774886878 1019.9858597285))
((0 . "LWPOLYLINE") (100 . "AcDbEntity") (8 . "PLANTS") (62 . 94) (370 . 13) (100 . "AcDbPolyline") (90 . 2) (70 . 0)
(43 . 0.0) (10 14524.8868778281 3921.5682126697) (10 14506.0335972851 3925.3393665158))
((0 . "LWPOLYLINE") (100 . "AcDbEntity") (8 . "PLANTS") (62 . 94) (370 . 13) (100 . "AcDbPolyline") (90 . 3) (70 . 0)
(43 . 0.0) (10 14506.0335972851 3925.3393665158) (10 14508.9085972851 3940.4158371041) (10 14517.3458144796
3947.963800905))
((0 . "LWPOLYLINE") (100 . "AcDbEntity") (8 . "PLANTS") (62 . 94) (370 . 13) (100 . "AcDbPolyline") (90 . 2) (70 . 0)
(43 . 0.0) (10 14506.0335972851 294.1176470588) (10 14513.5746606335 294.1176470588))
((0 . "LWPOLYLINE") (100 . "AcDbEntity") (8 . "PLANTS") (62 . 94) (370 . 13) (100 . "AcDbPolyline") (90 . 2) (70 . 0)
(43 . 0.0) (10 14506.0335972851 294.1176470588) (10 14506.0335972851 275.2630090498))
((0 . "LWPOLYLINE") (100 . "AcDbEntity") (8 . "PLANTS") (62 . 94) (370 . 13) (100 . "AcDbPolyline") (90 . 3) (70 . 0)
(43 . 0.0) (10 14506.0335972851 275.2630090498) (10 14513.581561086 268.9205882353) (10 14539.9702488688
263.9507918552))
((0 . "LWPOLYLINE") (100 . "AcDbEntity") (8 . "PLANTS") (62 . 94) (370 . 13) (100 . "AcDbPolyline") (90 . 2) (70 . 0)
(43 . 0.0) (10 14528.6580316742 980.3930995475) (10 14509.8035067873 980.3930995475))
((0 . "LWPOLYLINE") (100 . "AcDbEntity") (8 . "PLANTS") (62 . 94) (370 . 13) (100 . "AcDbPolyline") (90 . 2) (70 . 0)
(43 . 0.0) (10 14513.5746606335 294.1176470588) (10 14509.8035067873 350.6787330317))
((0 . "LWPOLYLINE") (100 . "AcDbEntity") (8 . "PLANTS") (62 . 94) (370 . 13) (100 . "AcDbPolyline") (90 . 2) (70 . 0)
(43 . 0.0) (10 14539.9702488688 365.7607466063) (10 14509.8035067873 350.6787330317))
((0 . "LWPOLYLINE") (100 . "AcDbEntity") (8 . "PLANTS") (62 . 94) (370 . 13) (100 . "AcDbPolyline") (90 . 3) (70 . 0)
(43 . 0.0) (10 14513.581293797 4034.6935632148) (10 14513.581561086 3993.2126696833) (10 14517.3458144796
3947.963800905))
((0 . "LWPOLYLINE") (100 . "AcDbEntity") (8 . "PLANTS") (62 . 94) (370 . 13) (100 . "AcDbPolyline") (90 . 3) (70 . 0)
(43 . 0.0) (10 14513.5746606335 3793.3639140271) (10 14518.4022624434 3759.4272624434) (10 14528.6580316742
3744.3438914027))
((0 . "LWPOLYLINE") (100 . "AcDbEntity") (8 . "PLANTS") (62 . 94) (370 . 13) (100 . "AcDbPolyline") (90 . 2) (70 . 0)
(43 . 0.0) (10 14513.5746606335 3793.3639140271) (10 14532.4279411765 3797.1338235294))
((0 . "LWPOLYLINE") (100 . "AcDbEntity") (8 . "PLANTS") (62 . 94) (370 . 13) (100 . "AcDbPolyline") (90 . 2) (70 . 0)
(43 . 0.0) (10 14543.740158371 294.1176470588) (10 14513.5746606335 294.1176470588))
((0 . "LWPOLYLINE") (100 . "AcDbEntity") (8 . "PLANTS") (62 . 94) (370 . 13) (100 . "AcDbPolyline") (90 . 3) (70 . 0)
(43 . 0.0) (10 14528.6580316742 3936.6515837104) (10 14524.8868778281 3944.1926470588) (10 14517.3458144796
3947.963800905))
((0 . "LWPOLYLINE") (100 . "AcDbEntity") (8 . "PLANTS") (62 . 94) (370 . 13) (100 . "AcDbPolyline") (90 . 2) (70 . 0)
(43 . 0.0) (10 14517.3458144796 1202.8655542986) (10 14517.3458144796 1063.3484162896))
((0 . "LWPOLYLINE") (100 . "AcDbEntity") (8 . "PLANTS") (62 . 94) (370 . 13) (100 . "AcDbPolyline") (90 . 2) (70 . 0)
(43 . 0.0) (10 14528.6575791855 1048.2664027149) (10 14517.3458144796 1063.3484162896))
((0 . "LWPOLYLINE") (100 . "AcDbEntity") (8 . "PLANTS") (62 . 94) (370 . 13) (100 . "AcDbPolyline") (90 . 3) (70 . 0)
(43 . 0.0) (10 14521.1157239819 1021.8693438914) (10 14531.3714932127 1003.0175339367) (10 14532.4279411765
991.7053167421))
((0 . "LWPOLYLINE") (100 . "AcDbEntity") (8 . "PLANTS") (62 . 94) (370 . 13) (100 . "AcDbPolyline") (90 . 3) (70 . 0)
(43 . 0.0) (10 14521.1157239819 1021.8693438914) (10 14528.6575791855 1033.181561086) (10 14528.6575791855
1048.2664027149))
((0 . "LWPOLYLINE") (100 . "AcDbEntity") (8 . "PLANTS") (62 . 94) (370 . 13) (100 . "AcDbPolyline") (90 . 2) (70 . 0)
(43 . 0.0) (10 14524.8868778281 3883.8616515837) (10 14524.8868778281 3921.5682126697))
((0 . "LWPOLYLINE") (100 . "AcDbEntity") (8 . "PLANTS") (62 . 94) (370 . 13) (100 . "AcDbPolyline") (90 . 3) (70 . 0)
(43 . 0.0) (10 14528.6580316742 3936.6515837104) (10 14528.6580316742 3925.3393665158) (10 14524.8868778281
3921.5682126697))
((0 . "LWPOLYLINE") (100 . "AcDbEntity") (8 . "PLANTS") (62 . 94) (370 . 13) (100 . "AcDbPolyline") (90 . 2) (70 . 0)
(43 . 0.0) (10 14524.8868778281 3883.8616515837) (10 14570.1357466063 3891.4027149321))
((0 . "LWPOLYLINE") (100 . "AcDbEntity") (8 . "PLANTS") (62 . 94) (370 . 13) (100 . "AcDbPolyline") (90 . 2) (70 . 0)
(43 . 0.0) (10 14528.6580316742 3744.3438914027) (10 14524.8868778281 3733.0316742081))
((0 . "LWPOLYLINE") (100 . "AcDbEntity") (8 . "PLANTS") (62 . 94) (370 . 13) (100 . "AcDbPolyline") (90 . 2) (70 . 0)
(43 . 0.0) (10 14524.8868778281 392.1578054299) (10 14539.9702488688 377.0729638009))
((0 . "LWPOLYLINE") (100 . "AcDbEntity") (8 . "PLANTS") (62 . 94) (370 . 13) (100 . "AcDbPolyline") (90 . 2) (70 . 0)
(43 . 0.0) (10 14526.7718325792 937.0277149321) (10 14528.6580316742 901.2075791855))
((0 . "LWPOLYLINE") (100 . "AcDbEntity") (8 . "PLANTS") (62 . 94) (370 . 13) (100 . "AcDbPolyline") (90 . 2) (70 . 0)
(43 . 0.0) (10 14528.6580316742 980.3930995475) (10 14526.7718325792 937.0277149321))
((0 . "LWPOLYLINE") (100 . "AcDbEntity") (8 . "PLANTS") (62 . 94) (370 . 13) (100 . "AcDbPolyline") (90 . 3) (70 . 0)
(43 . 0.0) (10 14526.7718325792 937.0277149321) (10 14536.1314479638 937.6421945701) (10 14566.3645927602
923.8320135747))
((0 . "LWPOLYLINE") (100 . "AcDbEntity") (8 . "PLANTS") (62 . 94) (370 . 13) (100 . "AcDbPolyline") (90 . 2) (70 . 0)
(43 . 0.0) (10 14570.1357466063 1048.2664027149) (10 14528.6575791855 1048.2664027149))
((0 . "LWPOLYLINE") (100 . "AcDbEntity") (8 . "PLANTS") (62 . 94) (370 . 13) (100 . "AcDbPolyline") (90 . 2) (70 . 0)
(43 . 0.0) (10 14570.1357466063 3947.963800905) (10 14528.6580316742 3936.6515837104))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.3218966453)
(40 . 0.4228132114) (40 . 0.7412902066) (40 . 1) (40 . 1) (40 . 1) (40 . 1) (10 14690.7989819005 3751.8849547511 0.0)
(10 14673.4999779372 3747.747111244 0.0) (10 14650.3054265703 3748.6677181012 0.0) (10 14610.8624258703 3739.6225663929
0.0) (10 14573.3120471328 3736.0402362694 0.0) (10 14542.3918373996 3750.7223279738 0.0) (10 14528.6580316742
3744.3438914028 0.0))
((0 . "LWPOLYLINE") (100 . "AcDbEntity") (8 . "PLANTS") (62 . 94) (370 . 13) (100 . "AcDbPolyline") (90 . 2) (70 . 0)
(43 . 0.0) (10 14528.6580316742 980.3930995475) (10 14532.4279411765 991.7053167421))
((0 . "LWPOLYLINE") (100 . "AcDbEntity") (8 . "PLANTS") (62 . 94) (370 . 13) (100 . "AcDbPolyline") (90 . 3) (70 . 0)
(43 . 0.0) (10 14566.3645927602 908.7471719457) (10 14555.0523755656 901.3608597285) (10 14528.6580316742
901.2075791855))
((0 . "LWPOLYLINE") (100 . "AcDbEntity") (8 . "PLANTS") (62 . 94) (370 . 13) (100 . "AcDbPolyline") (90 . 2) (70 . 0)
(43 . 0.0) (10 14619.1557692308 3789.592760181) (10 14532.4279411765 3797.1338235294))
((0 . "LWPOLYLINE") (100 . "AcDbEntity") (8 . "PLANTS") (62 . 94) (370 . 13) (100 . "AcDbPolyline") (90 . 3) (70 . 0)
(43 . 0.0) (10 14532.4279411765 3797.1338235294) (10 14543.8947963801 3831.0642533937) (10 14570.1357466063
3846.1538461538))
((0 . "LWPOLYLINE") (100 . "AcDbEntity") (8 . "PLANTS") (62 . 94) (370 . 13) (100 . "AcDbPolyline") (90 . 2) (70 . 0)
(43 . 0.0) (10 14532.4279411765 991.7053167421) (10 14566.3645927602 991.7053167421))
((0 . "LWPOLYLINE") (100 . "AcDbEntity") (8 . "PLANTS") (62 . 94) (370 . 13) (100 . "AcDbPolyline") (90 . 2) (70 . 0)
(43 . 0.0) (10 14539.9702488688 365.7607466063) (10 14539.9702488688 377.0729638009))
((0 . "LWPOLYLINE") (100 . "AcDbEntity") (8 . "PLANTS") (62 . 94) (370 . 13) (100 . "AcDbPolyline") (90 . 3) (70 . 0)
(43 . 0.0) (10 14539.9702488688 365.7607466063) (10 14547.3704751131 361.8363122172) (10 14555.0523755656
346.9089366516))
((0 . "LWPOLYLINE") (100 . "AcDbEntity") (8 . "PLANTS") (62 . 94) (370 . 13) (100 . "AcDbPolyline") (90 . 2) (70 . 0)
(43 . 0.0) (10 14539.9702488688 263.9507918552) (10 14543.740158371 245.0989819005))
((0 . "LWPOLYLINE") (100 . "AcDbEntity") (8 . "PLANTS") (62 . 94) (370 . 13) (100 . "AcDbPolyline") (90 . 3) (70 . 0)
(43 . 0.0) (10 14539.9702488688 263.9507918552) (10 14543.5923076923 271.5001131222) (10 14543.740158371
294.1176470588))
((0 . "LWPOLYLINE") (100 . "AcDbEntity") (8 . "PLANTS") (62 . 94) (370 . 13) (100 . "AcDbPolyline") (90 . 3) (70 . 0)
(43 . 0.0) (10 14543.740158371 294.1176470588) (10 14543.8878959276 320.5118778281) (10 14555.0523755656
346.9089366516))
((0 . "LWPOLYLINE") (100 . "AcDbEntity") (8 . "PLANTS") (62 . 94) (370 . 13) (100 . "AcDbPolyline") (90 . 2) (70 . 0)
(43 . 0.0) (10 14573.9069004525 245.0989819005) (10 14543.740158371 245.0989819005))
((0 . "LWPOLYLINE") (100 . "AcDbEntity") (8 . "PLANTS") (62 . 94) (370 . 13) (100 . "AcDbPolyline") (90 . 2) (70 . 0)
(43 . 0.0) (10 14562.5946832579 346.9089366516) (10 14555.0523755656 346.9089366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14562.5946832579 346.9089366516 0.0) (10 14589.0558870916 321.0381907606 0.0) (10 14573.6080972351
274.1142187898 0.0) (10 14573.9069004525 245.0989819005 0.0))
((0 . "LWPOLYLINE") (100 . "AcDbEntity") (8 . "PLANTS") (62 . 94) (370 . 13) (100 . "AcDbPolyline") (90 . 3) (70 . 0)
(43 . 0.0) (10 14588.9890271493 380.8455882353) (10 14581.3002262443 365.7607466063) (10 14562.5946832579
346.9089366516))
((0 . "LWPOLYLINE") (100 . "AcDbEntity") (8 . "PLANTS") (62 . 94) (370 . 13) (100 . "AcDbPolyline") (90 . 3) (70 . 0)
(43 . 0.0) (10 14566.3645927602 923.8320135747) (10 14570.1357466063 969.0808823529) (10 14566.3645927602
991.7053167421))
((0 . "LWPOLYLINE") (100 . "AcDbEntity") (8 . "PLANTS") (62 . 94) (370 . 13) (100 . "AcDbPolyline") (90 . 3) (70 . 0)
(43 . 0.0) (10 14566.3645927602 991.7053167421) (10 14569.9880090498 999.2524886878) (10 14570.1357466063
1040.7239819005))
((0 . "LWPOLYLINE") (100 . "AcDbEntity") (8 . "PLANTS") (62 . 94) (370 . 13) (100 . "AcDbPolyline") (90 . 2) (70 . 0)
(43 . 0.0) (10 14566.3645927602 908.7471719457) (10 14566.3645927602 923.8320135747))
((0 . "LWPOLYLINE") (100 . "AcDbEntity") (8 . "PLANTS") (62 . 94) (370 . 13) (100 . "AcDbPolyline") (90 . 2) (70 . 0)
(43 . 0.0) (10 14566.3645927602 908.7471719457) (10 14604.07239819 908.7471719457))
((0 . "LWPOLYLINE") (100 . "AcDbEntity") (8 . "PLANTS") (62 . 94) (370 . 13) (100 . "AcDbPolyline") (90 . 3) (70 . 0)
(43 . 0.0) (10 15260.1809954751 4015.8371040724) (10 15256.4167420814 4027.149321267) (10 15256.273158588
4142.9344817259))
((0 . "LWPOLYLINE") (100 . "AcDbEntity") (8 . "PLANTS") (62 . 94) (370 . 13) (100 . "AcDbPolyline") (90 . 3) (70 . 0)
(43 . 0.0) (10 14570.1357466063 3947.963800905) (10 14570.1288461538 4049.7737556561) (10 14568.8092130687
4057.7051962447))
((0 . "LWPOLYLINE") (100 . "AcDbEntity") (8 . "PLANTS") (62 . 94) (370 . 13) (100 . "AcDbPolyline") (90 . 2) (70 . 0)
(43 . 0.0) (10 14570.1357466063 3947.963800905) (10 14615.3846153846 3944.1926470588))
((0 . "LWPOLYLINE") (100 . "AcDbEntity") (8 . "PLANTS") (62 . 94) (370 . 13) (100 . "AcDbPolyline") (90 . 2) (70 . 0)
(43 . 0.0) (10 14570.1357466063 3947.963800905) (10 14570.1357466063 3891.4027149321))
((0 . "LWPOLYLINE") (100 . "AcDbEntity") (8 . "PLANTS") (62 . 94) (370 . 13) (100 . "AcDbPolyline") (90 . 3) (70 . 0)
(43 . 0.0) (10 14570.1357466063 3891.4027149321) (10 14576.6272624434 3887.47760181) (10 14581.4479638009
3876.3193438914))
((0 . "LWPOLYLINE") (100 . "AcDbEntity") (8 . "PLANTS") (62 . 94) (370 . 13) (100 . "AcDbPolyline") (90 . 3) (70 . 0)
(43 . 0.0) (10 14592.7601809955 3834.8416289593) (10 14577.6837104072 3836.0458144796) (10 14570.1357466063
3846.1538461538))
((0 . "LWPOLYLINE") (100 . "AcDbEntity") (8 . "PLANTS") (62 . 94) (370 . 13) (100 . "AcDbPolyline") (90 . 2) (70 . 0)
(43 . 0.0) (10 14581.4479638009 3876.3193438914) (10 14570.1357466063 3846.1538461538))
((0 . "LWPOLYLINE") (100 . "AcDbEntity") (8 . "PLANTS") (62 . 94) (370 . 13) (100 . "AcDbPolyline") (90 . 2) (70 . 0)
(43 . 0.0) (10 14570.1357466063 1048.2664027149) (10 14570.1357466063 1176.4705882353))
((0 . "LWPOLYLINE") (100 . "AcDbEntity") (8 . "PLANTS") (62 . 94) (370 . 13) (100 . "AcDbPolyline") (90 . 2) (70 . 0)
(43 . 0.0) (10 14570.1357466063 1048.2664027149) (10 14570.1357466063 1040.7239819005))
((0 . "LWPOLYLINE") (100 . "AcDbEntity") (8 . "PLANTS") (62 . 94) (370 . 13) (100 . "AcDbPolyline") (90 . 2) (70 . 0)
(43 . 0.0) (10 14604.07239819 1040.7239819005) (10 14570.1357466063 1040.7239819005))
((0 . "LWPOLYLINE") (100 . "AcDbEntity") (8 . "PLANTS") (62 . 94) (370 . 13) (100 . "AcDbPolyline") (90 . 2) (70 . 0)
(43 . 0.0) (10 14600.3012443439 241.3263574661) (10 14573.9069004525 245.0989819005))
((0 . "LWPOLYLINE") (100 . "AcDbEntity") (8 . "PLANTS") (62 . 94) (370 . 13) (100 . "AcDbPolyline") (90 . 2) (70 . 0)
(43 . 0.0) (10 14624.8118778281 3878.2055429864) (10 14581.4479638009 3876.3193438914))
((0 . "LWPOLYLINE") (100 . "AcDbEntity") (8 . "PLANTS") (62 . 94) (370 . 13) (100 . "AcDbPolyline") (90 . 2) (70 . 0)
(43 . 0.0) (10 14588.9890271493 380.8455882353) (10 14581.4479638009 407.2398190045))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14588.9890271493 380.8455882353 0.0) (10 14611.8691341948 380.2170640713 0.0) (10 14602.3147043016
413.3235573157 0.0) (10 14622.925678733 418.5520361991 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14600.3012443439 241.3263574661 0.0) (10 14613.8580485163 225.4673600072 0.0) (10 14635.334557757
235.7682012127 0.0) (10 14653.0924208145 233.7858597285 0.0))
((0 . "LWPOLYLINE") (100 . "AcDbEntity") (8 . "PLANTS") (62 . 94) (370 . 13) (100 . "AcDbPolyline") (90 . 2) (70 . 0)
(43 . 0.0) (10 14600.3012443439 241.3263574661) (10 14626.6968325792 290.3478506787))
((0 . "LWPOLYLINE") (100 . "AcDbEntity") (8 . "PLANTS") (62 . 94) (370 . 13) (100 . "AcDbPolyline") (90 . 2) (70 . 0)
(43 . 0.0) (10 14604.07239819 1040.7239819005) (10 14604.07239819 1010.5571266968))
((0 . "LWPOLYLINE") (100 . "AcDbEntity") (8 . "PLANTS") (62 . 94) (370 . 13) (100 . "AcDbPolyline") (90 . 2) (70 . 0)
(43 . 0.0) (10 14604.07239819 1040.7239819005) (10 14619.1557692308 1052.036199095))
((0 . "LWPOLYLINE") (100 . "AcDbEntity") (8 . "PLANTS") (62 . 94) (370 . 13) (100 . "AcDbPolyline") (90 . 2) (70 . 0)
(43 . 0.0) (10 14626.6968325792 1010.5571266968) (10 14604.07239819 1010.5571266968))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14604.07239819 908.7471719457 0.0) (10 14575.3232494837 944.8909767947 0.0) (10 14621.6493681783
976.3441566138 0.0) (10 14604.07239819 1010.5571266968 0.0))
((0 . "LWPOLYLINE") (100 . "AcDbEntity") (8 . "PLANTS") (62 . 94) (370 . 13) (100 . "AcDbPolyline") (90 . 2) (70 . 0)
(43 . 0.0) (10 14604.07239819 908.7471719457) (10 14653.0924208145 904.9773755656))
((0 . "LWPOLYLINE") (100 . "AcDbEntity") (8 . "PLANTS") (62 . 94) (370 . 13) (100 . "AcDbPolyline") (90 . 3) (70 . 0)
(43 . 0.0) (10 14615.3846153846 3944.1926470588) (10 14619.3781674208 3887.5645927602) (10 14624.8118778281
3878.2055429864))
((0 . "LWPOLYLINE") (100 . "AcDbEntity") (8 . "PLANTS") (62 . 94) (370 . 13) (100 . "AcDbPolyline") (90 . 3) (70 . 0)
(43 . 0.0) (10 14615.3846153846 3944.1926470588) (10 14619.1488687783 3955.5055429864) (10 14619.1658902463
4078.6871450687))
((0 . "LWPOLYLINE") (100 . "AcDbEntity") (8 . "PLANTS") (62 . 94) (370 . 13) (100 . "AcDbPolyline") (90 . 2) (70 . 0)
(43 . 0.0) (10 14626.6968325792 3778.2805429864) (10 14619.1557692308 3789.592760181))
((0 . "LWPOLYLINE") (100 . "AcDbEntity") (8 . "PLANTS") (62 . 94) (370 . 13) (100 . "AcDbPolyline") (90 . 3) (70 . 0)
(43 . 0.0) (10 14619.1557692308 3789.592760181) (10 14656.8623303167 3798.3385746606) (10 14671.9457013575
3808.446040724))
((0 . "LWPOLYLINE") (100 . "AcDbEntity") (8 . "PLANTS") (62 . 94) (370 . 13) (100 . "AcDbPolyline") (90 . 3) (70 . 0)
(43 . 0.0) (10 14626.6968325792 1010.5571266968) (10 14630.3133484163 1040.7239819005) (10 14619.1557692308
1052.036199095))
((0 . "LWPOLYLINE") (100 . "AcDbEntity") (8 . "PLANTS") (62 . 94) (370 . 13) (100 . "AcDbPolyline") (90 . 2) (70 . 0)
(43 . 0.0) (10 14619.1557692308 1052.036199095) (10 14622.925678733 1074.6606334842))
((0 . "LWPOLYLINE") (100 . "AcDbEntity") (8 . "PLANTS") (62 . 94) (370 . 13) (100 . "AcDbPolyline") (90 . 2) (70 . 0)
(43 . 0.0) (10 14622.925678733 1074.6606334842) (10 14620.6791519598 1151.1988855586))
((0 . "LWPOLYLINE") (100 . "AcDbEntity") (8 . "PLANTS") (62 . 94) (370 . 13) (100 . "AcDbPolyline") (90 . 2) (70 . 0)
(43 . 0.0) (10 14622.925678733 1074.6606334842) (10 14645.5501131222 1078.4304298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14671.9457013575 3815.9883484163 0.0) (10 14648.8076761393 3829.1208266369 0.0) (10 14632.339079141
3853.0162410809 0.0) (10 14624.8118778281 3878.2055429864 0.0))
((0 . "LWPOLYLINE") (100 . "AcDbEntity") (8 . "PLANTS") (62 . 94) (370 . 13) (100 . "AcDbPolyline") (90 . 3) (70 . 0)
(43 . 0.0) (10 14624.8118778281 3878.2055429864) (10 14645.5501131222 3885.0523755656) (10 14660.6334841629
3895.1738687783))
((0 . "LWPOLYLINE") (100 . "AcDbEntity") (8 . "PLANTS") (62 . 94) (370 . 13) (100 . "AcDbPolyline") (90 . 2) (70 . 0)
(43 . 0.0) (10 14638.0090497738 980.3930995475) (10 14626.6968325792 1010.5571266968))
((0 . "LWPOLYLINE") (100 . "AcDbEntity") (8 . "PLANTS") (62 . 94) (370 . 13) (100 . "AcDbPolyline") (90 . 3) (70 . 0)
(43 . 0.0) (10 14630.4679864253 312.9722850679) (10 14623.0803167421 305.4229638009) (10 14626.6968325792
290.3478506787))
((0 . "LWPOLYLINE") (100 . "AcDbEntity") (8 . "PLANTS") (62 . 94) (370 . 13) (100 . "AcDbPolyline") (90 . 3) (70 . 0)
(43 . 0.0) (10 14641.7802036199 301.6600678733) (10 14634.2378959276 291.5512443439) (10 14626.6968325792
290.3478506787))
((0 . "LWPOLYLINE") (100 . "AcDbEntity") (8 . "PLANTS") (62 . 94) (370 . 13) (100 . "AcDbPolyline") (90 . 2) (70 . 0)
(43 . 0.0) (10 14641.7802036199 301.6600678733) (10 14630.4679864253 312.9722850679))
((0 . "LWPOLYLINE") (100 . "AcDbEntity") (8 . "PLANTS") (62 . 94) (370 . 13) (100 . "AcDbPolyline") (90 . 3) (70 . 0)
(43 . 0.0) (10 14641.7802036199 346.9089366516) (10 14631.5244343891 331.8240950226) (10 14630.4679864253
312.9722850679))
((0 . "LWPOLYLINE") (100 . "AcDbEntity") (8 . "PLANTS") (62 . 94) (370 . 13) (100 . "AcDbPolyline") (90 . 2) (70 . 0)
(43 . 0.0) (10 14638.0090497738 980.3930995475) (10 14634.2378959276 969.0808823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14638.0090497738 980.3930995475 0.0) (10 14658.5518789695 970.7607386483 0.0) (10 14685.8597120003
1006.5165205476 0.0) (10 14694.5701357466 969.0808823529 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14641.7802036199 301.6600678733 0.0) (10 14665.4212865653 306.4998747575 0.0) (10 14672.5247863238
338.5673794635 0.0) (10 14702.111199095 331.8240950226 0.0))
((0 . "LWPOLYLINE") (100 . "AcDbEntity") (8 . "PLANTS") (62 . 94) (370 . 13) (100 . "AcDbPolyline") (90 . 3) (70 . 0)
(43 . 0.0) (10 14653.0924208145 904.9773755656) (10 14675.7168552036 901.2075791855) (10 14717.1945701357
904.9773755656))
((0 . "LWPOLYLINE") (100 . "AcDbEntity") (8 . "PLANTS") (62 . 94) (370 . 13) (100 . "AcDbPolyline") (90 . 3) (70 . 0)
(43 . 0.0) (10 14694.5701357466 969.0808823529) (10 14653.4597285068 932.2084841629) (10 14653.0924208145
904.9773755656))
((0 . "LWPOLYLINE") (100 . "AcDbEntity") (8 . "PLANTS") (62 . 94) (370 . 13) (100 . "AcDbPolyline") (90 . 3) (70 . 0)
(43 . 0.0) (10 14717.1945701357 245.0989819005) (10 14694.5701357466 233.7858597285) (10 14653.0924208145
233.7858597285))
((0 . "LWPOLYLINE") (100 . "AcDbEntity") (8 . "PLANTS") (62 . 94) (370 . 13) (100 . "AcDbPolyline") (90 . 3) (70 . 0)
(43 . 0.0) (10 14653.0924208145 233.7858597285) (10 14654.2966063348 263.9507918552) (10 14675.7168552036
282.8054298643))
((0 . "LWPOLYLINE") (100 . "AcDbEntity") (8 . "PLANTS") (62 . 94) (370 . 13) (100 . "AcDbPolyline") (90 . 2) (70 . 0)
(43 . 0.0) (10 14660.6334841629 3895.1738687783) (10 14656.8623303167 3906.4860859729))
((0 . "LWPOLYLINE") (100 . "AcDbEntity") (8 . "PLANTS") (62 . 94) (370 . 13) (100 . "AcDbPolyline") (90 . 2) (70 . 0)
(43 . 0.0) (10 14660.6334841629 3895.1738687783) (10 14675.7168552036 3876.3193438914))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3323772738) (40
. 1) (40 . 1) (40 . 1) (40 . 1) (10 14668.1745475113 1093.5152714933 0.0) (10 14680.1567734546 1106.8462919061 0.0) (10
14713.7376141169 1100.1101169695 0.0) (10 14734.6531969011 1030.0939674971 0.0) (10 14739.8190045249 1021.8693438914
0.0))
((0 . "LWPOLYLINE") (100 . "AcDbEntity") (8 . "PLANTS") (62 . 94) (370 . 13) (100 . "AcDbPolyline") (90 . 2) (70 . 0)
(43 . 0.0) (10 14671.9457013575 3815.9883484163) (10 14671.9457013575 3808.446040724))
((0 . "LWPOLYLINE") (100 . "AcDbEntity") (8 . "PLANTS") (62 . 94) (370 . 13) (100 . "AcDbPolyline") (90 . 2) (70 . 0)
(43 . 0.0) (10 14671.9457013575 3815.9883484163) (10 14698.3412895928 3838.6127828054))
((0 . "LWPOLYLINE") (100 . "AcDbEntity") (8 . "PLANTS") (62 . 94) (370 . 13) (100 . "AcDbPolyline") (90 . 3) (70 . 0)
(43 . 0.0) (10 14690.7989819005 3800.9049773756) (10 14679.4936651584 3802.10260181) (10 14671.9457013575
3808.446040724))
((0 . "LWPOLYLINE") (100 . "AcDbEntity") (8 . "PLANTS") (62 . 94) (370 . 13) (100 . "AcDbPolyline") (90 . 3) (70 . 0)
(43 . 0.0) (10 14675.7168552036 1025.6419683258) (10 14690.7989819005 1029.399321267) (10 14705.8823529412
1025.6419683258))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14698.3412895928 429.8642533937 0.0) (10 14672.986570261 417.4754725013 0.0) (10 14691.931129551
390.3522580476 0.0) (10 14675.7168552036 373.3031674208 0.0))
((0 . "LWPOLYLINE") (100 . "AcDbEntity") (8 . "PLANTS") (62 . 94) (370 . 13) (100 . "AcDbPolyline") (90 . 2) (70 . 0)
(43 . 0.0) (10 14683.257918552 460.0311085973) (10 14698.3412895928 471.3433257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14690.7989819005 3800.9049773756 0.0) (10 14732.9315235643 3794.894558252 0.0) (10 14778.9857188938
3786.4337819025 0.0) (10 14819.0045248869 3804.6761312217 0.0))
((0 . "LWPOLYLINE") (100 . "AcDbEntity") (8 . "PLANTS") (62 . 94) (370 . 13) (100 . "AcDbPolyline") (90 . 2) (70 . 0)
(43 . 0.0) (10 14690.7989819005 3800.9049773756) (10 14690.7989819005 3751.8849547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14811.4634615385 3751.8849547511 0.0) (10 14769.3422974853 3812.7010897731 0.0) (10 14730.286493587
3731.0678847747 0.0) (10 14690.7989819005 3751.8849547511 0.0))
((0 . "LWPOLYLINE") (100 . "AcDbEntity") (8 . "PLANTS") (62 . 94) (370 . 13) (100 . "AcDbPolyline") (90 . 3) (70 . 0)
(43 . 0.0) (10 14747.3600678733 984.1628959276) (10 14709.6535067873 970.129638009) (10 14694.5701357466
969.0808823529))
((0 . "LWPOLYLINE") (100 . "AcDbEntity") (8 . "PLANTS") (62 . 94) (370 . 13) (100 . "AcDbPolyline") (90 . 2) (70 . 0)
(43 . 0.0) (10 14698.3412895928 3898.9437782805) (10 14709.6535067873 3902.7149321267))
((0 . "LWPOLYLINE") (100 . "AcDbEntity") (8 . "PLANTS") (62 . 94) (370 . 13) (100 . "AcDbPolyline") (90 . 3) (70 . 0)
(43 . 0.0) (10 14739.8190045249 3831.0704751131) (10 14713.4234162896 3831.2254524887) (10 14698.3412895928
3838.6127828054))
((0 . "LWPOLYLINE") (100 . "AcDbEntity") (8 . "PLANTS") (62 . 94) (370 . 13) (100 . "AcDbPolyline") (90 . 3) (70 . 0)
(43 . 0.0) (10 14720.9657239819 3868.778280543) (10 14702.2658371041 3849.925) (10 14698.3412895928 3838.6127828054))
((0 . "LWPOLYLINE") (100 . "AcDbEntity") (8 . "PLANTS") (62 . 94) (370 . 13) (100 . "AcDbPolyline") (90 . 2) (70 . 0)
(43 . 0.0) (10 14709.6535067873 467.5707013575) (10 14698.3412895928 471.3433257919))
((0 . "LWPOLYLINE") (100 . "AcDbEntity") (8 . "PLANTS") (62 . 94) (370 . 13) (100 . "AcDbPolyline") (90 . 3) (70 . 0)
(43 . 0.0) (10 14724.7356334842 505.2799773756) (10 14706.0369909502 493.9601809955) (10 14698.3412895928
471.3433257919))
((0 . "LWPOLYLINE") (100 . "AcDbEntity") (8 . "PLANTS") (62 . 94) (370 . 13) (100 . "AcDbPolyline") (90 . 2) (70 . 0)
(43 . 0.0) (10 14705.8823529412 324.2845022624) (10 14702.111199095 331.8240950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14773.7556561086 412.8959276018 0.0) (10 14743.6197076829 393.9109476561 0.0) (10 14699.2575058587
376.3012207981 0.0) (10 14702.111199095 331.8240950226 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14751.1312217195 275.2630090498 0.0) (10 14761.0592849948 301.4711433122 0.0) (10 14738.3634936385
332.8228441758 0.0) (10 14705.8823529412 324.2845022624 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14705.8823529412 324.2845022624 0.0) (10 14720.4085750611 298.0555410706 0.0) (10 14686.7493517225
264.4387489232 0.0) (10 14717.1945701358 245.0989819004 0.0))
((0 . "LWPOLYLINE") (100 . "AcDbEntity") (8 . "PLANTS") (62 . 94) (370 . 13) (100 . "AcDbPolyline") (90 . 2) (70 . 0)
(43 . 0.0) (10 14717.1945701357 3898.9437782805) (10 14709.6535067873 3902.7149321267))
((0 . "LWPOLYLINE") (100 . "AcDbEntity") (8 . "PLANTS") (62 . 94) (370 . 13) (100 . "AcDbPolyline") (90 . 3) (70 . 0)
(43 . 0.0) (10 14717.1945701357 3932.8804298643) (10 14709.8082579186 3921.5682126697) (10 14709.6535067873
3902.7149321267))
((0 . "LWPOLYLINE") (100 . "AcDbEntity") (8 . "PLANTS") (62 . 94) (370 . 13) (100 . "AcDbPolyline") (90 . 2) (70 . 0)
(43 . 0.0) (10 14720.9657239819 3868.778280543) (10 14717.1945701357 3898.9437782805))
((0 . "LWPOLYLINE") (100 . "AcDbEntity") (8 . "PLANTS") (62 . 94) (370 . 13) (100 . "AcDbPolyline") (90 . 2) (70 . 0)
(43 . 0.0) (10 14717.1945701357 3898.9437782805) (10 14736.0478506787 3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14830.3167420815 908.7471719457 0.0) (10 14796.3513557711 892.5163023717 0.0) (10 14751.0872178953
886.5944642889 0.0) (10 14717.1945701357 904.9773755656 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14754.9023755656 984.1628959276 0.0) (10 14767.9925644158 945.8122405058 0.0) (10 14713.6964015639
941.7269780333 0.0) (10 14717.1945701357 904.9773755656 0.0))
((0 . "LWPOLYLINE") (100 . "AcDbEntity") (8 . "PLANTS") (62 . 94) (370 . 13) (100 . "AcDbPolyline") (90 . 2) (70 . 0)
(43 . 0.0) (10 14728.5067873303 245.0989819005) (10 14717.1945701357 245.0989819005))
((0 . "LWPOLYLINE") (100 . "AcDbEntity") (8 . "PLANTS") (62 . 94) (370 . 13) (100 . "AcDbPolyline") (90 . 3) (70 . 0)
(43 . 0.0) (10 14720.9657239819 3868.778280543) (10 14751.124321267 3863.809841629) (10 14758.6722850679
3857.4660633484))
((0 . "LWPOLYLINE") (100 . "AcDbEntity") (8 . "PLANTS") (62 . 94) (370 . 13) (100 . "AcDbPolyline") (90 . 3) (70 . 0)
(43 . 0.0) (10 14777.5268099548 456.2584841629) (10 14739.8259049774 482.80260181) (10 14724.7356334842 505.2799773756))
((0 . "LWPOLYLINE") (100 . "AcDbEntity") (8 . "PLANTS") (62 . 94) (370 . 13) (100 . "AcDbPolyline") (90 . 2) (70 . 0)
(43 . 0.0) (10 14734.2904111992 527.5736624792) (10 14724.7356334842 505.2799773756))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14728.5067873303 245.0989819004 0.0) (10 14736.8737761859 225.1150786946 0.0) (10 14757.7006521558
235.2103024673 0.0) (10 14773.7556561086 233.7858597285 0.0))
((0 . "LWPOLYLINE") (100 . "AcDbEntity") (8 . "PLANTS") (62 . 94) (370 . 13) (100 . "AcDbPolyline") (90 . 2) (70 . 0)
(43 . 0.0) (10 14728.5067873303 245.0989819005) (10 14751.1312217195 275.2630090498))
((0 . "LWPOLYLINE") (100 . "AcDbEntity") (8 . "PLANTS") (62 . 94) (370 . 13) (100 . "AcDbPolyline") (90 . 2) (70 . 0)
(43 . 0.0) (10 14747.3600678733 984.1628959276) (10 14739.8190045249 1021.8693438914))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14739.8190045249 1021.8693438914 0.0) (10 14784.2730832813 1016.2850364914 0.0) (10 14792.2727163865
1063.0593591021 0.0) (10 14788.8390271493 1093.5152714932 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14766.2145927602 3951.7349547511 0.0) (10 14743.0629138012 3950.4539123217 0.0) (10 14769.1126822093
3914.0484284156 0.0) (10 14743.590158371 3921.5682126697 0.0))
((0 . "LWPOLYLINE") (100 . "AcDbEntity") (8 . "PLANTS") (62 . 94) (370 . 13) (100 . "AcDbPolyline") (90 . 2) (70 . 0)
(43 . 0.0) (10 14747.3600678733 984.1628959276) (10 14754.9023755656 984.1628959276))
((0 . "LWPOLYLINE") (100 . "AcDbEntity") (8 . "PLANTS") (62 . 94) (370 . 13) (100 . "AcDbPolyline") (90 . 3) (70 . 0)
(43 . 0.0) (10 14751.1312217195 275.2630090498) (10 14768.7872171946 267.575) (10 14773.7556561086 233.7858597285))
((0 . "LWPOLYLINE") (100 . "AcDbEntity") (8 . "PLANTS") (62 . 94) (370 . 13) (100 . "AcDbPolyline") (90 . 3) (70 . 0)
(43 . 0.0) (10 14800.1512443439 986.0492081448) (10 14766.2145927602 987.7856334842) (10 14754.9023755656
984.1628959276))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4765992928) (40
. 1) (40 . 1) (40 . 1) (40 . 1) (10 14766.2145927602 3951.7349547511 0.0) (10 14779.4745107009 3946.430257667 0.0) (10
14808.949585966 3942.2856337535 0.0) (10 14837.1104397178 3932.1163170682 0.0) (10 14852.9411764706 3932.8804298642
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14766.2145927602 3951.7349547511 0.0) (10 14767.6331502493 4014.8911735454 0.0) (10 14874.2830782319
3991.184373991 0.0) (10 14852.9411764706 3932.8804298643 0.0))
((0 . "LWPOLYLINE") (100 . "AcDbEntity") (8 . "PLANTS") (62 . 94) (370 . 13) (100 . "AcDbPolyline") (90 . 3) (70 . 0)
(43 . 0.0) (10 14769.9845022624 3834.8416289593) (10 14777.5337104072 3831.2188914027) (10 14807.6923076923
3831.0704751131))
((0 . "LWPOLYLINE") (100 . "AcDbEntity") (8 . "PLANTS") (62 . 94) (370 . 13) (100 . "AcDbPolyline") (90 . 3) (70 . 0)
(43 . 0.0) (10 14773.7556561086 412.8959276018) (10 14787.7826923077 384.6153846154) (10 14792.6089366516
346.9089366516))
((0 . "LWPOLYLINE") (100 . "AcDbEntity") (8 . "PLANTS") (62 . 94) (370 . 13) (100 . "AcDbPolyline") (90 . 2) (70 . 0)
(43 . 0.0) (10 14777.5268099548 456.2584841629) (10 14773.7556561086 412.8959276018))
((0 . "LWPOLYLINE") (100 . "AcDbEntity") (8 . "PLANTS") (62 . 94) (370 . 13) (100 . "AcDbPolyline") (90 . 3) (70 . 0)
(43 . 0.0) (10 14819.0045248869 422.3218325792) (10 14785.0678733032 418.4007918552) (10 14773.7556561086
412.8959276018))
((0 . "LWPOLYLINE") (100 . "AcDbEntity") (8 . "PLANTS") (62 . 94) (370 . 13) (100 . "AcDbPolyline") (90 . 3) (70 . 0)
(43 . 0.0) (10 14773.7556561086 321.7699095023) (10 14782.4938914027 339.3596153846) (10 14792.6089366516
346.9089366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14773.7556561086 233.7858597285 0.0) (10 14799.1548365787 234.8393081058 0.0) (10 14829.1685145963
223.2955808557 0.0) (10 14843.5139140271 254.5248868778 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14819.0045248869 422.3218325792 0.0) (10 14824.3832472525 444.7437078542 0.0) (10 14803.5320236461
479.7320694651 0.0) (10 14777.5268099547 456.2584841629 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14807.6923076923 3853.6949095023 0.0) (10 14794.1761381353 3854.8367301878 0.0) (10 14777.8661139894
3875.1151746273 0.0) (10 14788.8390271493 3887.631561086 0.0))
((0 . "LWPOLYLINE") (100 . "AcDbEntity") (8 . "PLANTS") (62 . 94) (370 . 13) (100 . "AcDbPolyline") (90 . 2) (70 . 0)
(43 . 0.0) (10 14800.1512443439 986.0492081448) (10 14792.6089366516 961.5384615385))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14792.6089366516 346.9089366516 0.0) (10 14822.9013097907 333.033284914 0.0) (10 14804.1925095192
286.465481265 0.0) (10 14837.8578054299 275.2630090498 0.0))
((0 . "LWPOLYLINE") (100 . "AcDbEntity") (8 . "PLANTS") (62 . 94) (370 . 13) (100 . "AcDbPolyline") (90 . 3) (70 . 0)
(43 . 0.0) (10 14800.1512443439 986.0492081448) (10 14819.0045248869 976.7688914027) (10 14856.7123303167
972.850678733))
((0 . "LWPOLYLINE") (100 . "AcDbEntity") (8 . "PLANTS") (62 . 94) (370 . 13) (100 . "AcDbPolyline") (90 . 3) (70 . 0)
(43 . 0.0) (10 14800.1512443439 986.0492081448) (10 14819.7515837104 1014.3297511312) (10 14819.0045248869
1025.6419683258))
((0 . "LWPOLYLINE") (100 . "AcDbEntity") (8 . "PLANTS") (62 . 94) (370 . 13) (100 . "AcDbPolyline") (90 . 2) (70 . 0)
(43 . 0.0) (10 14807.6923076923 3831.0704751131) (10 14807.6923076923 3853.6949095023))
((0 . "LWPOLYLINE") (100 . "AcDbEntity") (8 . "PLANTS") (62 . 94) (370 . 13) (100 . "AcDbPolyline") (90 . 2) (70 . 0)
(43 . 0.0) (10 14807.6923076923 3853.6949095023) (10 14822.775678733 3865.0071266968))
((0 . "LWPOLYLINE") (100 . "AcDbEntity") (8 . "PLANTS") (62 . 94) (370 . 13) (100 . "AcDbPolyline") (90 . 3) (70 . 0)
(43 . 0.0) (10 14819.0045248869 3804.6761312217) (10 14814.0360859729 3823.5231900452) (10 14807.6923076923
3831.0704751131))
((0 . "LWPOLYLINE") (100 . "AcDbEntity") (8 . "PLANTS") (62 . 94) (370 . 13) (100 . "AcDbPolyline") (90 . 3) (70 . 0)
(43 . 0.0) (10 14811.4634615385 3751.8849547511) (10 14807.8469457014 3736.8028280543) (10 14809.052583586
3733.0316742081))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14811.4634615385 3751.8849547511 0.0) (10 14824.6506124631 3778.7775703716 0.0) (10 14872.1498117143
3753.8751699791 0.0) (10 14851.3112873987 3733.0316742081 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.497711978) (40 .
1) (40 . 1) (40 . 1) (40 . 1) (10 14815.2333710408 1052.036199095 0.0) (10 14833.4599125875 1062.0481624141 0.0) (10
14815.198163761 1101.9181133013 0.0) (10 14853.8271421732 1121.4397192572 0.0) (10 14852.9411764707 1138.7641402715
0.0))
((0 . "LWPOLYLINE") (100 . "AcDbEntity") (8 . "PLANTS") (62 . 94) (370 . 13) (100 . "AcDbPolyline") (90 . 3) (70 . 0)
(43 . 0.0) (10 14819.0045248869 3804.6761312217) (10 14879.3395927602 3804.8239819005) (10 14892.5339366516
3808.446040724))
((0 . "LWPOLYLINE") (100 . "AcDbEntity") (8 . "PLANTS") (62 . 94) (370 . 13) (100 . "AcDbPolyline") (90 . 2) (70 . 0)
(43 . 0.0) (10 14819.0045248869 422.3218325792) (10 14847.2850678733 386.5016968326))
((0 . "LWPOLYLINE") (100 . "AcDbEntity") (8 . "PLANTS") (62 . 94) (370 . 13) (100 . "AcDbPolyline") (90 . 2) (70 . 0)
(43 . 0.0) (10 14822.775678733 1131.221719457) (10 14834.0878959276 1153.8461538462))
((0 . "LWPOLYLINE") (100 . "AcDbEntity") (8 . "PLANTS") (62 . 94) (370 . 13) (100 . "AcDbPolyline") (90 . 2) (70 . 0)
(43 . 0.0) (10 14830.3167420814 908.7471719457) (10 14830.3167420814 916.2895927602))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14830.3167420815 908.7471719457 0.0) (10 14853.7869881122 898.3049165714 0.0) (10 14887.2616939405
892.3557731265 0.0) (10 14905.7311085973 916.2895927602 0.0))
((0 . "LWPOLYLINE") (100 . "AcDbEntity") (8 . "PLANTS") (62 . 94) (370 . 13) (100 . "AcDbPolyline") (90 . 2) (70 . 0)
(43 . 0.0) (10 14834.0878959276 377.0729638009) (10 14847.2850678733 386.5016968326))
((0 . "LWPOLYLINE") (100 . "AcDbEntity") (8 . "PLANTS") (62 . 94) (370 . 13) (100 . "AcDbPolyline") (90 . 3) (70 . 0)
(43 . 0.0) (10 14843.5139140271 254.5248868778) (10 14838.0800904977 263.8838235294) (10 14837.8578054299
275.2630090498))
((0 . "LWPOLYLINE") (100 . "AcDbEntity") (8 . "PLANTS") (62 . 94) (370 . 13) (100 . "AcDbPolyline") (90 . 3) (70 . 0)
(43 . 0.0) (10 14888.7627828054 305.4298642534) (10 14864.2533936652 300.4614253394) (10 14837.8578054299
275.2630090498))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14928.3555429864 252.6385746607 0.0) (10 14908.1700716121 221.521845041 0.0) (10 14865.9126361478
231.14843172 0.0) (10 14843.5139140272 254.5248868779 0.0))
((0 . "LWPOLYLINE") (100 . "AcDbEntity") (8 . "PLANTS") (62 . 94) (370 . 13) (100 . "AcDbPolyline") (90 . 3) (70 . 0)
(43 . 0.0) (10 14888.7627828054 305.4298642534) (10 14874.5092760181 282.9531674208) (10 14843.5139140271
254.5248868778))
((0 . "LWPOLYLINE") (100 . "AcDbEntity") (8 . "PLANTS") (62 . 94) (370 . 13) (100 . "AcDbPolyline") (90 . 3) (70 . 0)
(43 . 0.0) (10 14847.2850678733 386.5016968326) (10 14852.9411764706 380.8455882353) (10 14860.482239819
380.8455882353))
((0 . "LWPOLYLINE") (100 . "AcDbEntity") (8 . "PLANTS") (62 . 94) (370 . 13) (100 . "AcDbPolyline") (90 . 3) (70 . 0)
(43 . 0.0) (10 14847.2850678733 386.5016968326) (10 14864.2602941176 406.1834841629) (10 14879.3367647059
411.0096153846))
((0 . "LWPOLYLINE") (100 . "AcDbEntity") (8 . "PLANTS") (62 . 94) (370 . 13) (100 . "AcDbPolyline") (90 . 3) (70 . 0)
(43 . 0.0) (10 14849.1700226244 1044.4937782805) (10 14860.6368778281 1018.0995475113) (10 14879.3367647059
1003.0175339367))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14852.9411764706 3989.4415158371 0.0) (10 14876.2755955779 3992.7730577144 0.0) (10 14888.4913613403
4015.2501966357 0.0) (10 14892.3368189393 4035.7539449871 0.0))
((0 . "LWPOLYLINE") (100 . "AcDbEntity") (8 . "PLANTS") (62 . 94) (370 . 13) (100 . "AcDbPolyline") (90 . 2) (70 . 0)
(43 . 0.0) (10 14860.482239819 3921.5682126697) (10 14852.9411764706 3932.8804298643))
((0 . "LWPOLYLINE") (100 . "AcDbEntity") (8 . "PLANTS") (62 . 94) (370 . 13) (100 . "AcDbPolyline") (90 . 2) (70 . 0)
(43 . 0.0) (10 14856.7123303167 972.850678733) (10 14883.1066742081 972.850678733))
((0 . "LWPOLYLINE") (100 . "AcDbEntity") (8 . "PLANTS") (62 . 94) (370 . 13) (100 . "AcDbPolyline") (90 . 2) (70 . 0)
(43 . 0.0) (10 14860.482239819 987.9326923077) (10 14856.7123303167 972.850678733))
((0 . "LWPOLYLINE") (100 . "AcDbEntity") (8 . "PLANTS") (62 . 94) (370 . 13) (100 . "AcDbPolyline") (90 . 2) (70 . 0)
(43 . 0.0) (10 14860.482239819 3921.5682126697) (10 14928.3555429864 3917.7983031674))
((0 . "LWPOLYLINE") (100 . "AcDbEntity") (8 . "PLANTS") (62 . 94) (370 . 13) (100 . "AcDbPolyline") (90 . 2) (70 . 0)
(43 . 0.0) (10 14860.482239819 3921.5682126697) (10 14860.482239819 3906.4860859729))
((0 . "LWPOLYLINE") (100 . "AcDbEntity") (8 . "PLANTS") (62 . 94) (370 . 13) (100 . "AcDbPolyline") (90 . 3) (70 . 0)
(43 . 0.0) (10 14886.8778280543 3853.6949095023) (10 14880.2316742081 3880.0904977376) (10 14860.482239819
3906.4860859729))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14886.8778280543 3853.6949095023 0.0) (10 14850.144402204 3830.5047139678 0.0) (10 14814.0664243469
3895.9817837925 0.0) (10 14860.482239819 3906.4860859729 0.0))
((0 . "LWPOLYLINE") (100 . "AcDbEntity") (8 . "PLANTS") (62 . 94) (370 . 13) (100 . "AcDbPolyline") (90 . 2) (70 . 0)
(43 . 0.0) (10 14888.7627828054 305.4298642534) (10 14860.482239819 380.8455882353))
((0 . "LWPOLYLINE") (100 . "AcDbEntity") (8 . "PLANTS") (62 . 94) (370 . 13) (100 . "AcDbPolyline") (90 . 3) (70 . 0)
(43 . 0.0) (10 14860.482239819 380.8455882353) (10 14878.1326923077 395.92760181) (10 14879.3367647059 411.0096153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14898.1900452489 1006.7873303167 0.0) (10 14899.0248741154 1029.1930198092 0.0) (10 14900.3373916536
1068.0281846506 0.0) (10 14871.7944570136 1074.6606334842 0.0))
((0 . "LWPOLYLINE") (100 . "AcDbEntity") (8 . "PLANTS") (62 . 94) (370 . 13) (100 . "AcDbPolyline") (90 . 2) (70 . 0)
(43 . 0.0) (10 14883.1066742081 972.850678733) (10 14879.3367647059 1003.0175339367))
((0 . "LWPOLYLINE") (100 . "AcDbEntity") (8 . "PLANTS") (62 . 94) (370 . 13) (100 . "AcDbPolyline") (90 . 2) (70 . 0)
(43 . 0.0) (10 14898.1900452489 1006.7873303167) (10 14879.3367647059 1003.0175339367))
((0 . "LWPOLYLINE") (100 . "AcDbEntity") (8 . "PLANTS") (62 . 94) (370 . 13) (100 . "AcDbPolyline") (90 . 2) (70 . 0)
(43 . 0.0) (10 14879.3367647059 411.0096153846) (10 14886.8778280543 433.6340497738))
((0 . "LWPOLYLINE") (100 . "AcDbEntity") (8 . "PLANTS") (62 . 94) (370 . 13) (100 . "AcDbPolyline") (90 . 2) (70 . 0)
(43 . 0.0) (10 14883.1066742081 972.850678733) (10 14909.5022624434 953.996040724))
((0 . "LWPOLYLINE") (100 . "AcDbEntity") (8 . "PLANTS") (62 . 94) (370 . 13) (100 . "AcDbPolyline") (90 . 3) (70 . 0)
(43 . 0.0) (10 14894.4188914027 3838.6127828054) (10 14886.8778280543 3846.1538461538) (10 14886.8778280543
3853.6949095023))
((0 . "LWPOLYLINE") (100 . "AcDbEntity") (8 . "PLANTS") (62 . 94) (370 . 13) (100 . "AcDbPolyline") (90 . 2) (70 . 0)
(43 . 0.0) (10 14905.7311085973 916.2895927602) (10 14886.8778280543 935.1442307692))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14924.5856334842 392.1578054299 0.0) (10 14926.6275766638 413.806914115 0.0) (10 14908.5537073168
434.4150134885 0.0) (10 14886.8778280543 433.6340497738 0.0))
((0 . "LWPOLYLINE") (100 . "AcDbEntity") (8 . "PLANTS") (62 . 94) (370 . 13) (100 . "AcDbPolyline") (90 . 3) (70 . 0)
(43 . 0.0) (10 14886.8778280543 433.6340497738) (10 14890.7968325792 490.1951357466) (10 14898.1900452489
505.2799773756))
((0 . "LWPOLYLINE") (100 . "AcDbEntity") (8 . "PLANTS") (62 . 94) (370 . 13) (100 . "AcDbPolyline") (90 . 2) (70 . 0)
(43 . 0.0) (10 14888.7627828054 305.4298642534) (10 14928.3555429864 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15003.7711538462 3736.8028280543 0.0) (10 15000.8577474183 3794.9419219965 0.0) (10 14926.8929096788
3777.3675274199 0.0) (10 14892.5339366516 3808.446040724 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14913.2734162896 3733.0316742081 0.0) (10 14886.5838560756 3745.1769453314 0.0) (10 14877.385193271
3782.0687160869 0.0) (10 14892.5339366516 3808.446040724 0.0))
((0 . "LWPOLYLINE") (100 . "AcDbEntity") (8 . "PLANTS") (62 . 94) (370 . 13) (100 . "AcDbPolyline") (90 . 2) (70 . 0)
(43 . 0.0) (10 14892.5339366516 3808.446040724) (10 14894.4188914027 3838.6127828054))
((0 . "LWPOLYLINE") (100 . "AcDbEntity") (8 . "PLANTS") (62 . 94) (370 . 13) (100 . "AcDbPolyline") (90 . 3) (70 . 0)
(43 . 0.0) (10 14928.3555429864 3846.1538461538) (10 14909.5022624434 3845.9992081448) (10 14894.4188914027
3838.6127828054))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14898.1900452489 1006.7873303167 0.0) (10 14922.0358724236 1003.0738544939 0.0) (10 14937.3735795214
965.7664671798 0.0) (10 14909.5022624434 953.996040724 0.0))
((0 . "LWPOLYLINE") (100 . "AcDbEntity") (8 . "PLANTS") (62 . 94) (370 . 13) (100 . "AcDbPolyline") (90 . 2) (70 . 0)
(43 . 0.0) (10 14917.0433257919 916.2895927602) (10 14905.7311085973 916.2895927602))
((0 . "LWPOLYLINE") (100 . "AcDbEntity") (8 . "PLANTS") (62 . 94) (370 . 13) (100 . "AcDbPolyline") (90 . 2) (70 . 0)
(43 . 0.0) (10 14917.0433257919 931.3716063348) (10 14909.5022624434 953.996040724))
((0 . "LWPOLYLINE") (100 . "AcDbEntity") (8 . "PLANTS") (62 . 94) (370 . 13) (100 . "AcDbPolyline") (90 . 2) (70 . 0)
(43 . 0.0) (10 14924.5856334842 3944.1926470588) (10 14913.2734162896 3951.7349547511))
((0 . "LWPOLYLINE") (100 . "AcDbEntity") (8 . "PLANTS") (62 . 94) (370 . 13) (100 . "AcDbPolyline") (90 . 2) (70 . 0)
(43 . 0.0) (10 14917.0433257919 916.2895927602) (10 14917.0433257919 931.3716063348))
((0 . "LWPOLYLINE") (100 . "AcDbEntity") (8 . "PLANTS") (62 . 94) (370 . 13) (100 . "AcDbPolyline") (90 . 3) (70 . 0)
(43 . 0.0) (10 14969.8345022624 946.4564479638) (10 14939.667760181 941.6350678733) (10 14917.0433257919
931.3716063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14917.0433257919 916.2895927602 0.0) (10 14933.7435178479 896.3684430377 0.0) (10 14971.2782755587
890.3229461834 0.0) (10 14988.6877828054 912.5197963801 0.0))
((0 . "LWPOLYLINE") (100 . "AcDbEntity") (8 . "PLANTS") (62 . 94) (370 . 13) (100 . "AcDbPolyline") (90 . 2) (70 . 0)
(43 . 0.0) (10 14924.5856334842 3944.1926470588) (10 14928.3555429864 3917.7983031674))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4544613348) (40
. 1) (40 . 1) (40 . 1) (40 . 1) (10 14924.5856334842 3944.1926470588 0.0) (10 14953.3135485049 3948.2934561654 0.0) (10
14938.7896079969 4066.635825823 0.0) (10 15045.2740250445 3945.1524440549 0.0) (10 15033.9366515837 3944.1926470588
0.0))
((0 . "LWPOLYLINE") (100 . "AcDbEntity") (8 . "PLANTS") (62 . 94) (370 . 13) (100 . "AcDbPolyline") (90 . 2) (70 . 0)
(43 . 0.0) (10 14939.667760181 3917.7983031674) (10 14928.3555429864 3917.7983031674))
((0 . "LWPOLYLINE") (100 . "AcDbEntity") (8 . "PLANTS") (62 . 94) (370 . 13) (100 . "AcDbPolyline") (90 . 3) (70 . 0)
(43 . 0.0) (10 14928.3555429864 3846.1538461538) (10 14966.0633484163 3813.2738687783) (10 14981.146719457
3808.446040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 14928.3555429864 3846.1538461538 0.0) (10 14956.5984140356 3876.8575455238 0.0) (10 15006.5132190252
3880.5311918721 0.0) (10 15045.2488687783 3872.5494343891 0.0))
((0 . "LWPOLYLINE") (100 . "AcDbEntity") (8 . "PLANTS") (62 . 94) (370 . 13) (100 . "AcDbPolyline") (90 . 2) (70 . 0)
(43 . 0.0) (10 14928.3555429864 305.4298642534) (10 14928.3555429864 271.4932126697))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3356668757)
(40 . 0.611833528) (40 . 1) (40 . 1) (40 . 1) (40 . 1) (10 14928.3555429864 305.4298642534 0.0) (10 14927.8644526136
323.2517545491 0.0) (10 14942.8802347605 348.7354021448 0.0) (10 14966.0301467402 393.5150082767 0.0) (10
14986.1048695833 420.0230553432 0.0) (10 15003.7711538462 429.8642533937 0.0))
((0 . "LWPOLYLINE") (100 . "AcDbEntity") (8 . "PLANTS") (62 . 94) (370 . 13) (100 . "AcDbPolyline") (90 . 3) (70 . 0)
(43 . 0.0) (10 14973.6044117647 263.9507918552) (10 14947.2100678733 271.3454751131) (10 14928.3555429864
271.4932126697))
((0 . "LWPOLYLINE") (100 . "AcDbEntity") (8 . "PLANTS") (62 . 94) (370 . 13) (100 . "AcDbPolyline") (90 . 2) (70 . 0)
(43 . 0.0) (10 14928.3555429864 252.6385746606) (10 14928.3555429864 271.4932126697))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15033.9366515837 252.6385746606 0.0) (10 15006.4372877803 242.2556904685 0.0) (10 14950.8918639254
211.7610183582 0.0) (10 14928.3555429864 252.6385746606 0.0))
((0 . "LWPOLYLINE") (100 . "AcDbEntity") (8 . "PLANTS") (62 . 94) (370 . 13) (100 . "AcDbPolyline") (90 . 3) (70 . 0)
(43 . 0.0) (10 14939.667760181 3910.2559954751) (10 14935.8978506787 3910.2559954751) (10 14932.1266968326
3902.7149321267))
((0 . "LWPOLYLINE") (100 . "AcDbEntity") (8 . "PLANTS") (62 . 94) (370 . 13) (100 . "AcDbPolyline") (90 . 2) (70 . 0)
(43 . 0.0) (10 14939.667760181 3910.2559954751) (10 14939.667760181 3917.7983031674))
((0 . "LWPOLYLINE") (100 . "AcDbEntity") (8 . "PLANTS") (62 . 94) (370 . 13) (100 . "AcDbPolyline") (90 . 3) (70 . 0)
(43 . 0.0) (10 14981.146719457 3951.7349547511) (10 14977.2209276018 3941.4781674208) (10 14939.667760181
3917.7983031674))
((0 . "LWPOLYLINE") (100 . "AcDbEntity") (8 . "PLANTS") (62 . 94) (370 . 13) (100 . "AcDbPolyline") (90 . 3) (70 . 0)
(43 . 0.0) (10 14939.667760181 3910.2559954751) (10 14954.7511312217 3902.8695701357) (10 15000 3914.0271493213))
((0 . "LWPOLYLINE") (100 . "AcDbEntity") (8 . "PLANTS") (62 . 94) (370 . 13) (100 . "AcDbPolyline") (90 . 3) (70 . 0)
(43 . 0.0) (10 14988.6877828054 3714.1783936652) (10 14983.7193438914 3691.553959276) (10 14983.537214663
3691.3719903021))
((0 . "LWPOLYLINE") (100 . "AcDbEntity") (8 . "PLANTS") (62 . 94) (370 . 13) (100 . "AcDbPolyline") (90 . 3) (70 . 0)
(43 . 0.0) (10 14980.317872742 3717.8044818637) (10 14981.1398190045 3717.8004524887) (10 14988.6877828054
3714.1783936652))
((0 . "LWPOLYLINE") (100 . "AcDbEntity") (8 . "PLANTS") (62 . 94) (370 . 13) (100 . "AcDbPolyline") (90 . 2) (70 . 0)
(43 . 0.0) (10 14988.6877828054 912.5197963801) (10 14969.8345022624 946.4564479638))
((0 . "LWPOLYLINE") (100 . "AcDbEntity") (8 . "PLANTS") (62 . 94) (370 . 13) (100 . "AcDbPolyline") (90 . 2) (70 . 0)
(43 . 0.0) (10 14969.8345022624 946.4564479638) (10 14973.6044117647 972.850678733))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.2497996699)
(40 . 0.5336957748) (40 . 0.7338103837) (40 . 1) (40 . 1) (40 . 1) (40 . 1) (10 14973.6044117647 972.850678733 0.0) (10
14962.2939338084 972.5685216868 0.0) (10 14947.2088468186 1017.1572073208 0.0) (10 14995.6116607473 1014.3551281528 0.0)
(10 14999.4994915818 1053.6915658544 0.0) (10 15021.708621446 1063.6028730325 0.0) (10 15041.4777149321 1048.2664027149
0.0))
((0 . "LWPOLYLINE") (100 . "AcDbEntity") (8 . "PLANTS") (62 . 94) (370 . 13) (100 . "AcDbPolyline") (90 . 2) (70 . 0)
(43 . 0.0) (10 15026.3955882353 984.1628959276) (10 14973.6044117647 972.850678733))
((0 . "LWPOLYLINE") (100 . "AcDbEntity") (8 . "PLANTS") (62 . 94) (370 . 13) (100 . "AcDbPolyline") (90 . 2) (70 . 0)
(43 . 0.0) (10 15000 3819.7582579186) (10 14984.9166289593 3834.8416289593))
((0 . "LWPOLYLINE") (100 . "AcDbEntity") (8 . "PLANTS") (62 . 94) (370 . 13) (100 . "AcDbPolyline") (90 . 3) (70 . 0)
(43 . 0.0) (10 15003.7711538462 3736.8028280543) (10 14995.1792986425 3718.103280543) (10 14988.6877828054
3714.1783936652))
((0 . "LWPOLYLINE") (100 . "AcDbEntity") (8 . "PLANTS") (62 . 94) (370 . 13) (100 . "AcDbPolyline") (90 . 2) (70 . 0)
(43 . 0.0) (10 14988.6877828054 912.5197963801) (10 15007.5410633484 912.5197963801))
((0 . "LWPOLYLINE") (100 . "AcDbEntity") (8 . "PLANTS") (62 . 94) (370 . 13) (100 . "AcDbPolyline") (90 . 2) (70 . 0)
(43 . 0.0) (10 15000 444.9462669683) (10 15003.7711538462 429.8642533937))
((0 . "LWPOLYLINE") (100 . "AcDbEntity") (8 . "PLANTS") (62 . 94) (370 . 13) (100 . "AcDbPolyline") (90 . 3) (70 . 0)
(43 . 0.0) (10 15067.8733031674 3755.6561085973) (10 15030.1654977376 3741.6290723982) (10 15003.7711538462
3736.8028280543))
((0 . "LWPOLYLINE") (100 . "AcDbEntity") (8 . "PLANTS") (62 . 94) (370 . 13) (100 . "AcDbPolyline") (90 . 3) (70 . 0)
(43 . 0.0) (10 15049.0200226244 388.3851809955) (10 15019.007918552 403.617081448) (10 15003.7711538462 429.8642533937))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15098.038800905 912.5197963801 0.0) (10 15067.4035715305 918.699372824 0.0) (10 15033.8174422431
882.2777933008 0.0) (10 15007.5410633484 912.5197963801 0.0))
((0 . "LWPOLYLINE") (100 . "AcDbEntity") (8 . "PLANTS") (62 . 94) (370 . 13) (100 . "AcDbPolyline") (90 . 3) (70 . 0)
(43 . 0.0) (10 15030.1654977376 969.0808823529) (10 15029.1090497738 950.2262443439) (10 15007.5410633484
912.5197963801))
((0 . "LWPOLYLINE") (100 . "AcDbEntity") (8 . "PLANTS") (62 . 94) (370 . 13) (100 . "AcDbPolyline") (90 . 2) (70 . 0)
(43 . 0.0) (10 15018.853280543 343.1363122172) (10 15011.3122171946 343.1363122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15015.0833710407 3797.1338235294 0.0) (10 15023.4112298316 3788.1996055647 0.0) (10 15041.6491269794
3785.3843089568 0.0) (10 15049.0200226244 3797.1338235294 0.0))
((0 . "LWPOLYLINE") (100 . "AcDbEntity") (8 . "PLANTS") (62 . 94) (370 . 13) (100 . "AcDbPolyline") (90 . 2) (70 . 0)
(43 . 0.0) (10 15026.3955882353 297.8874434389) (10 15018.853280543 343.1363122172))
((0 . "LWPOLYLINE") (100 . "AcDbEntity") (8 . "PLANTS") (62 . 94) (370 . 13) (100 . "AcDbPolyline") (90 . 3) (70 . 0)
(43 . 0.0) (10 15049.0200226244 350.6787330317) (10 15030.1654977376 349.62239819) (10 15018.853280543 343.1363122172))
((0 . "LWPOLYLINE") (100 . "AcDbEntity") (8 . "PLANTS") (62 . 94) (370 . 13) (100 . "AcDbPolyline") (90 . 3) (70 . 0)
(43 . 0.0) (10 15026.3955882353 984.1628959276) (10 15030.1654977376 980.3930995475) (10 15030.1654977376
969.0808823529))
((0 . "LWPOLYLINE") (100 . "AcDbEntity") (8 . "PLANTS") (62 . 94) (370 . 13) (100 . "AcDbPolyline") (90 . 3) (70 . 0)
(43 . 0.0) (10 15052.7899321267 1010.5571266968) (10 15037.7147058824 1002.8691176471) (10 15026.3955882353
984.1628959276))
((0 . "LWPOLYLINE") (100 . "AcDbEntity") (8 . "PLANTS") (62 . 94) (370 . 13) (100 . "AcDbPolyline") (90 . 3) (70 . 0)
(43 . 0.0) (10 15043.5533617615 458.5632764383) (10 15055.5047511312 426.0944570136) (10 15060.332239819 399.69739819))
((0 . "LWPOLYLINE") (100 . "AcDbEntity") (8 . "PLANTS") (62 . 94) (370 . 13) (100 . "AcDbPolyline") (90 . 3) (70 . 0)
(43 . 0.0) (10 15026.3955882353 297.8874434389) (10 15036.5037330317 290.3402714932) (10 15041.4777149321
260.1809954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15033.9366515837 252.6385746606 0.0) (10 15017.9762268205 259.8089904895 0.0) (10 15011.0749681908
287.0644724032 0.0) (10 15026.3955882353 297.8874434389 0.0))
((0 . "LWPOLYLINE") (100 . "AcDbEntity") (8 . "PLANTS") (62 . 94) (370 . 13) (100 . "AcDbPolyline") (90 . 3) (70 . 0)
(43 . 0.0) (10 15105.5811085973 972.850678733) (10 15071.6444570136 976.4734162896) (10 15030.1654977376
969.0808823529))
((0 . "LWPOLYLINE") (100 . "AcDbEntity") (8 . "PLANTS") (62 . 94) (370 . 13) (100 . "AcDbPolyline") (90 . 3) (70 . 0)
(43 . 0.0) (10 15033.9366515837 3944.1926470588) (10 15038.7642533937 3906.4860859729) (10 15049.0200226244
3887.631561086))
((0 . "LWPOLYLINE") (100 . "AcDbEntity") (8 . "PLANTS") (62 . 94) (370 . 13) (100 . "AcDbPolyline") (90 . 2) (70 . 0)
(43 . 0.0) (10 15033.9366515837 3944.1926470588) (10 15052.7899321267 3947.963800905))
((0 . "LWPOLYLINE") (100 . "AcDbEntity") (8 . "PLANTS") (62 . 94) (370 . 13) (100 . "AcDbPolyline") (90 . 2) (70 . 0)
(43 . 0.0) (10 15033.9366515837 252.6385746606) (10 15041.4777149321 252.6385746606))
((0 . "LWPOLYLINE") (100 . "AcDbEntity") (8 . "PLANTS") (62 . 94) (370 . 13) (100 . "AcDbPolyline") (90 . 2) (70 . 0)
(43 . 0.0) (10 15037.7078054299 1074.6606334842) (10 15041.4777149321 1048.2664027149))
((0 . "LWPOLYLINE") (100 . "AcDbEntity") (8 . "PLANTS") (62 . 94) (370 . 13) (100 . "AcDbPolyline") (90 . 2) (70 . 0)
(43 . 0.0) (10 15052.7899321267 1044.4937782805) (10 15041.4777149321 1048.2664027149))
((0 . "LWPOLYLINE") (100 . "AcDbEntity") (8 . "PLANTS") (62 . 94) (370 . 13) (100 . "AcDbPolyline") (90 . 2) (70 . 0)
(43 . 0.0) (10 15041.4777149321 260.1809954751) (10 15041.4777149321 252.6385746606))
((0 . "LWPOLYLINE") (100 . "AcDbEntity") (8 . "PLANTS") (62 . 94) (370 . 13) (100 . "AcDbPolyline") (90 . 2) (70 . 0)
(43 . 0.0) (10 15071.6444570136 275.2630090498) (10 15041.4777149321 260.1809954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15109.3510180996 233.7867647059 0.0) (10 15086.0453342915 226.2405762442 0.0) (10 15055.5423373463
228.8422248524 0.0) (10 15041.4777149321 252.6385746606 0.0))
((0 . "LWPOLYLINE") (100 . "AcDbEntity") (8 . "PLANTS") (62 . 94) (370 . 13) (100 . "AcDbPolyline") (90 . 2) (70 . 0)
(43 . 0.0) (10 15045.2488687783 3853.6949095023) (10 15045.2488687783 3872.5494343891))
((0 . "LWPOLYLINE") (100 . "AcDbEntity") (8 . "PLANTS") (62 . 94) (370 . 13) (100 . "AcDbPolyline") (90 . 3) (70 . 0)
(43 . 0.0) (10 15049.0200226244 3887.631561086) (10 15049.0200226244 3876.3193438914) (10 15045.2488687783
3872.5494343891))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15045.2488687783 3853.6949095023 0.0) (10 15075.7405520657 3840.1047677545 0.0) (10 15112.970986057
3831.6093842236 0.0) (10 15135.7466063348 3804.6761312217 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15049.0200226244 3797.1338235294 0.0) (10 15049.0694737251 3811.2411665078 0.0) (10 15028.7286257889
3840.639344996 0.0) (10 15045.2488687783 3853.6949095023 0.0))
((0 . "LWPOLYLINE") (100 . "AcDbEntity") (8 . "PLANTS") (62 . 94) (370 . 13) (100 . "AcDbPolyline") (90 . 2) (70 . 0)
(43 . 0.0) (10 15049.0200226244 3887.631561086) (10 15082.9566742081 3891.4027149321))
((0 . "LWPOLYLINE") (100 . "AcDbEntity") (8 . "PLANTS") (62 . 94) (370 . 13) (100 . "AcDbPolyline") (90 . 3) (70 . 0)
(43 . 0.0) (10 15049.0200226244 3797.1338235294) (10 15060.1845022624 3789.5865384615) (10 15071.6444570136
3770.739479638))
((0 . "LWPOLYLINE") (100 . "AcDbEntity") (8 . "PLANTS") (62 . 94) (370 . 13) (100 . "AcDbPolyline") (90 . 2) (70 . 0)
(43 . 0.0) (10 15049.0200226244 350.6787330317) (10 15049.0200226244 388.3851809955))
((0 . "LWPOLYLINE") (100 . "AcDbEntity") (8 . "PLANTS") (62 . 94) (370 . 13) (100 . "AcDbPolyline") (90 . 2) (70 . 0)
(43 . 0.0) (10 15060.332239819 399.69739819) (10 15049.0200226244 388.3851809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15071.6444570136 275.2630090498 0.0) (10 15072.3899059508 300.7582489413 0.0) (10 15070.786327814
333.1612239438 0.0) (10 15049.0200226244 350.6787330317 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15120.6632352941 3684.0116515837 0.0) (10 15127.5043702178 3644.500938675 0.0) (10 15088.266526302
3618.0086198888 0.0) (10 15052.7899321267 3623.6806561086 0.0))
((0 . "LWPOLYLINE") (100 . "AcDbEntity") (8 . "PLANTS") (62 . 94) (370 . 13) (100 . "AcDbPolyline") (90 . 2) (70 . 0)
(43 . 0.0) (10 15052.7899321267 1010.5571266968) (10 15052.7899321267 1044.4937782805))
((0 . "LWPOLYLINE") (100 . "AcDbEntity") (8 . "PLANTS") (62 . 94) (370 . 13) (100 . "AcDbPolyline") (90 . 3) (70 . 0)
(43 . 0.0) (10 15052.7899321267 1044.4937782805) (10 15075.2596153846 1053.2272624434) (10 15079.185520362
1059.5786199095))
((0 . "LWPOLYLINE") (100 . "AcDbEntity") (8 . "PLANTS") (62 . 94) (370 . 13) (100 . "AcDbPolyline") (90 . 2) (70 . 0)
(43 . 0.0) (10 15052.7899321267 1010.5571266968) (10 15103.6949095023 1008.6736425339))
((0 . "LWPOLYLINE") (100 . "AcDbEntity") (8 . "PLANTS") (62 . 94) (370 . 13) (100 . "AcDbPolyline") (90 . 2) (70 . 0)
(43 . 0.0) (10 15060.332239819 399.69739819) (10 15075.4143665158 399.69739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15131.9754524887 3725.4906108597 0.0) (10 15113.8652173453 3698.777920226 0.0) (10 15061.3889598167
3723.9641897438 0.0) (10 15067.8733031674 3755.6561085973 0.0))
((0 . "LWPOLYLINE") (100 . "AcDbEntity") (8 . "PLANTS") (62 . 94) (370 . 13) (100 . "AcDbPolyline") (90 . 2) (70 . 0)
(43 . 0.0) (10 15067.8733031674 3755.6561085973) (10 15071.6444570136 3770.739479638))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15135.7466063349 3789.592760181 0.0) (10 15122.7524427934 3767.0328242598 0.0) (10 15092.8705572051
3770.3088071316 0.0) (10 15071.6444570136 3770.739479638 0.0))
((0 . "LWPOLYLINE") (100 . "AcDbEntity") (8 . "PLANTS") (62 . 94) (370 . 13) (100 . "AcDbPolyline") (90 . 2) (70 . 0)
(43 . 0.0) (10 15071.6444570136 275.2630090498) (10 15101.8099547511 275.2630090498))
((0 . "LWPOLYLINE") (100 . "AcDbEntity") (8 . "PLANTS") (62 . 94) (370 . 13) (100 . "AcDbPolyline") (90 . 2) (70 . 0)
(43 . 0.0) (10 15086.7265837104 3533.182239819) (10 15075.4143665158 3525.6412895928))
((0 . "LWPOLYLINE") (100 . "AcDbEntity") (8 . "PLANTS") (62 . 94) (370 . 13) (100 . "AcDbPolyline") (90 . 3) (70 . 0)
(43 . 0.0) (10 15090.4977375566 354.4485294118) (10 15084.153959276 361.9978506787) (10 15075.4143665158 399.69739819))
((0 . "LWPOLYLINE") (100 . "AcDbEntity") (8 . "PLANTS") (62 . 94) (370 . 13) (100 . "AcDbPolyline") (90 . 2) (70 . 0)
(43 . 0.0) (10 15128.2055429864 426.0944570136) (10 15075.4143665158 399.69739819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15086.7265837104 1112.367081448 0.0) (10 15080.6377382138 1104.6863894531 0.0) (10 15072.2902000485
1092.1865656554 0.0) (10 15079.185520362 1082.2030542986 0.0))
((0 . "LWPOLYLINE") (100 . "AcDbEntity") (8 . "PLANTS") (62 . 94) (370 . 13) (100 . "AcDbPolyline") (90 . 3) (70 . 0)
(43 . 0.0) (10 15109.3510180995 3865.0071266968) (10 15090.6454751131 3876.3262443439) (10 15082.9566742081
3891.4027149321))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5007083615) (40
. 1) (40 . 1) (40 . 1) (40 . 1) (10 15147.0588235293 3880.0904977375 0.0) (10 15137.1833091715 3883.3027674895 0.0) (10
15116.2738984053 3901.5168386935 0.0) (10 15093.7858148087 3903.5541154874 0.0) (10 15082.9566742081 3891.4027149321
0.0))
((0 . "LWPOLYLINE") (100 . "AcDbEntity") (8 . "PLANTS") (62 . 94) (370 . 13) (100 . "AcDbPolyline") (90 . 2) (70 . 0)
(43 . 0.0) (10 15086.7265837104 3985.6716063348) (10 15131.9754524887 3993.2126696833))
((0 . "LWPOLYLINE") (100 . "AcDbEntity") (8 . "PLANTS") (62 . 94) (370 . 13) (100 . "AcDbPolyline") (90 . 3) (70 . 0)
(43 . 0.0) (10 15090.4977375566 354.4485294118) (10 15091.7019230769 320.5118778281) (10 15105.5811085973
305.4298642534))
((0 . "LWPOLYLINE") (100 . "AcDbEntity") (8 . "PLANTS") (62 . 94) (370 . 13) (100 . "AcDbPolyline") (90 . 2) (70 . 0)
(43 . 0.0) (10 15090.4977375566 354.4485294118) (10 15101.8099547511 358.2211538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15203.6199095023 912.5197963801 0.0) (10 15172.9232205949 905.9041601473 0.0) (10 15124.3305407889
882.0382706841 0.0) (10 15098.038800905 912.5197963801 0.0))
((0 . "LWPOLYLINE") (100 . "AcDbEntity") (8 . "PLANTS") (62 . 94) (370 . 13) (100 . "AcDbPolyline") (90 . 2) (70 . 0)
(43 . 0.0) (10 15098.038800905 912.5197963801) (10 15109.3510180995 950.2262443439))
((0 . "LWPOLYLINE") (100 . "AcDbEntity") (8 . "PLANTS") (62 . 94) (370 . 13) (100 . "AcDbPolyline") (90 . 2) (70 . 0)
(43 . 0.0) (10 15120.6632352941 343.1363122172) (10 15101.8099547511 358.2211538462))
((0 . "LWPOLYLINE") (100 . "AcDbEntity") (8 . "PLANTS") (62 . 94) (370 . 13) (100 . "AcDbPolyline") (90 . 2) (70 . 0)
(43 . 0.0) (10 15109.3510180995 388.3851809955) (10 15101.8099547511 358.2211538462))
((0 . "LWPOLYLINE") (100 . "AcDbEntity") (8 . "PLANTS") (62 . 94) (370 . 13) (100 . "AcDbPolyline") (90 . 3) (70 . 0)
(43 . 0.0) (10 15109.3510180995 233.7867647059) (10 15109.2031674208 252.6385746606) (10 15101.8099547511
275.2630090498))
((0 . "LWPOLYLINE") (100 . "AcDbEntity") (8 . "PLANTS") (62 . 94) (370 . 13) (100 . "AcDbPolyline") (90 . 3) (70 . 0)
(43 . 0.0) (10 15101.8099547511 275.2630090498) (10 15105.4333710407 282.8123303167) (10 15105.5811085973
305.4298642534))
((0 . "LWPOLYLINE") (100 . "AcDbEntity") (8 . "PLANTS") (62 . 94) (370 . 13) (100 . "AcDbPolyline") (90 . 2) (70 . 0)
(43 . 0.0) (10 15103.6949095023 1008.6736425339) (10 15116.8933257919 1006.7873303167))
((0 . "LWPOLYLINE") (100 . "AcDbEntity") (8 . "PLANTS") (62 . 94) (370 . 13) (100 . "AcDbPolyline") (90 . 2) (70 . 0)
(43 . 0.0) (10 15103.6949095023 1008.6736425339) (10 15105.5811085973 972.850678733))
((0 . "LWPOLYLINE") (100 . "AcDbEntity") (8 . "PLANTS") (62 . 94) (370 . 13) (100 . "AcDbPolyline") (90 . 3) (70 . 0)
(43 . 0.0) (10 15116.8933257919 1063.3484162896) (10 15102.8662895928 1025.6419683258) (10 15103.6949095023
1008.6736425339))
((0 . "LWPOLYLINE") (100 . "AcDbEntity") (8 . "PLANTS") (62 . 94) (370 . 13) (100 . "AcDbPolyline") (90 . 2) (70 . 0)
(43 . 0.0) (10 15105.5811085973 3416.2895927602) (10 15109.3510180995 3427.6018099548))
((0 . "LWPOLYLINE") (100 . "AcDbEntity") (8 . "PLANTS") (62 . 94) (370 . 13) (100 . "AcDbPolyline") (90 . 2) (70 . 0)
(43 . 0.0) (10 15105.5811085973 972.850678733) (10 15109.3510180995 950.2262443439))
((0 . "LWPOLYLINE") (100 . "AcDbEntity") (8 . "PLANTS") (62 . 94) (370 . 13) (100 . "AcDbPolyline") (90 . 2) (70 . 0)
(43 . 0.0) (10 15116.8933257919 305.4298642534) (10 15105.5811085973 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15169.6832579185 972.850678733 0.0) (10 15160.001514808 950.0925355798 0.0) (10 15131.2185316023
942.7166783086 0.0) (10 15109.3510180996 950.2262443439 0.0))
((0 . "LWPOLYLINE") (100 . "AcDbEntity") (8 . "PLANTS") (62 . 94) (370 . 13) (100 . "AcDbPolyline") (90 . 3) (70 . 0)
(43 . 0.0) (10 15109.3510180995 233.7867647059) (10 15169.6832579186 233.9338235294) (10 15188.5350678733
237.556561086))
((0 . "LWPOLYLINE") (100 . "AcDbEntity") (8 . "PLANTS") (62 . 94) (370 . 13) (100 . "AcDbPolyline") (90 . 2) (70 . 0)
(43 . 0.0) (10 15116.8933257919 305.4298642534) (10 15135.7466063348 297.8874434389))
((0 . "LWPOLYLINE") (100 . "AcDbEntity") (8 . "PLANTS") (62 . 94) (370 . 13) (100 . "AcDbPolyline") (90 . 2) (70 . 0)
(43 . 0.0) (10 15120.6632352941 343.1363122172) (10 15116.8933257919 305.4298642534))
((0 . "LWPOLYLINE") (100 . "AcDbEntity") (8 . "PLANTS") (62 . 94) (370 . 13) (100 . "AcDbPolyline") (90 . 3) (70 . 0)
(43 . 0.0) (10 15120.6632352941 343.1363122172) (10 15153.4095022624 384.6153846154) (10 15162.1421945701
414.782239819))
((0 . "LWPOLYLINE") (100 . "AcDbEntity") (8 . "PLANTS") (62 . 94) (370 . 13) (100 . "AcDbPolyline") (90 . 2) (70 . 0)
(43 . 0.0) (10 15131.9754524887 3514.3290723982) (10 15124.4343891403 3506.7873303167))
((0 . "LWPOLYLINE") (100 . "AcDbEntity") (8 . "PLANTS") (62 . 94) (370 . 13) (100 . "AcDbPolyline") (90 . 3) (70 . 0)
(43 . 0.0) (10 15158.371040724 3469.0802036199) (10 15128.3602941176 3464.1110859729) (10 15124.4343891403
3457.7679864253))
((0 . "LWPOLYLINE") (100 . "AcDbEntity") (8 . "PLANTS") (62 . 94) (370 . 13) (100 . "AcDbPolyline") (90 . 2) (70 . 0)
(43 . 0.0) (10 15131.9754524887 4008.296040724) (10 15128.2055429864 4015.8371040724))
((0 . "LWPOLYLINE") (100 . "AcDbEntity") (8 . "PLANTS") (62 . 94) (370 . 13) (100 . "AcDbPolyline") (90 . 2) (70 . 0)
(43 . 0.0) (10 15162.1421945701 414.782239819) (10 15128.2055429864 426.0944570136))
((0 . "LWPOLYLINE") (100 . "AcDbEntity") (8 . "PLANTS") (62 . 94) (370 . 13) (100 . "AcDbPolyline") (90 . 2) (70 . 0)
(43 . 0.0) (10 15128.2055429864 426.0944570136) (10 15135.7466063348 448.7188914027))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15154.5998868778 4049.7737556561 0.0) (10 15140.1343200978 4043.8423185483 0.0) (10 15120.3112306977
4062.3087032551 0.0) (10 15131.9754524887 4076.1693438914 0.0))
((0 . "LWPOLYLINE") (100 . "AcDbEntity") (8 . "PLANTS") (62 . 94) (370 . 13) (100 . "AcDbPolyline") (90 . 2) (70 . 0)
(43 . 0.0) (10 15131.9754524887 4008.296040724) (10 15131.9754524887 3993.2126696833))
((0 . "LWPOLYLINE") (100 . "AcDbEntity") (8 . "PLANTS") (62 . 94) (370 . 13) (100 . "AcDbPolyline") (90 . 3) (70 . 0)
(43 . 0.0) (10 15131.9754524887 4008.296040724) (10 15149.6259049774 4015.9851809955) (10 15154.5998868778
4049.7737556561))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3740110013) (40
. 1) (40 . 1) (40 . 1) (40 . 1) (10 15131.9754524887 3993.2126696833 0.0) (10 15144.1385741338 3984.41732154 0.0) (10
15145.278046942 3951.8434411097 0.0) (10 15150.449468064 3916.049407703 0.0) (10 15165.9121040724 3898.9437782805 0.0))
((0 . "LWPOLYLINE") (100 . "AcDbEntity") (8 . "PLANTS") (62 . 94) (370 . 13) (100 . "AcDbPolyline") (90 . 2) (70 . 0)
(43 . 0.0) (10 15131.9754524887 3514.3290723982) (10 15165.9121040724 3514.3290723982))
((0 . "LWPOLYLINE") (100 . "AcDbEntity") (8 . "PLANTS") (62 . 94) (370 . 13) (100 . "AcDbPolyline") (90 . 3) (70 . 0)
(43 . 0.0) (10 15165.9121040724 3536.9535067873) (10 15139.6725113122 3539.5197963801) (10 15131.9754524887
3514.3290723982))
((0 . "LWPOLYLINE") (100 . "AcDbEntity") (8 . "PLANTS") (62 . 94) (370 . 13) (100 . "AcDbPolyline") (90 . 2) (70 . 0)
(43 . 0.0) (10 15169.6832579186 4072.3981900452) (10 15160.6735712621 4091.4187497718))
((0 . "LWPOLYLINE") (100 . "AcDbEntity") (8 . "PLANTS") (62 . 94) (370 . 13) (100 . "AcDbPolyline") (90 . 2) (70 . 0)
(43 . 0.0) (10 15135.7466063348 3789.592760181) (10 15135.7466063348 3804.6761312217))
((0 . "LWPOLYLINE") (100 . "AcDbEntity") (8 . "PLANTS") (62 . 94) (370 . 13) (100 . "AcDbPolyline") (90 . 3) (70 . 0)
(43 . 0.0) (10 15135.7466063348 3804.6761312217) (10 15145.8616515837 3815.9883484163) (10 15150.8299773756
3834.8416289593))
((0 . "LWPOLYLINE") (100 . "AcDbEntity") (8 . "PLANTS") (62 . 94) (370 . 13) (100 . "AcDbPolyline") (90 . 2) (70 . 0)
(43 . 0.0) (10 15135.7466063348 3789.592760181) (10 15162.1421945701 3785.8216063348))
((0 . "LWPOLYLINE") (100 . "AcDbEntity") (8 . "PLANTS") (62 . 94) (370 . 13) (100 . "AcDbPolyline") (90 . 3) (70 . 0)
(43 . 0.0) (10 15135.7466063348 3657.6173076923) (10 15143.146719457 3655.1980769231) (10 15150.8299773756
3668.9295248869))
((0 . "LWPOLYLINE") (100 . "AcDbEntity") (8 . "PLANTS") (62 . 94) (370 . 13) (100 . "AcDbPolyline") (90 . 3) (70 . 0)
(43 . 0.0) (10 15188.5350678733 3585.9728506787) (10 15150.8299773756 3596.0808823529) (10 15135.7466063348
3585.9728506787))
((0 . "LWPOLYLINE") (100 . "AcDbEntity") (8 . "PLANTS") (62 . 94) (370 . 13) (100 . "AcDbPolyline") (90 . 2) (70 . 0)
(43 . 0.0) (10 15158.371040724 1067.1182126697) (10 15139.517760181 1033.181561086))
((0 . "LWPOLYLINE") (100 . "AcDbEntity") (8 . "PLANTS") (62 . 94) (370 . 13) (100 . "AcDbPolyline") (90 . 3) (70 . 0)
(43 . 0.0) (10 15169.6832579186 418.5520361991) (10 15171.2009049774 460.0311085973) (10 15153.0684940045
475.3059741053))
((0 . "LWPOLYLINE") (100 . "AcDbEntity") (8 . "PLANTS") (62 . 94) (370 . 13) (100 . "AcDbPolyline") (90 . 3) (70 . 0)
(43 . 0.0) (10 15150.8299773756 3834.8416289593) (10 15147.206561086 3846.1538461538) (10 15147.0588235294
3880.0904977376))
((0 . "LWPOLYLINE") (100 . "AcDbEntity") (8 . "PLANTS") (62 . 94) (370 . 13) (100 . "AcDbPolyline") (90 . 3) (70 . 0)
(43 . 0.0) (10 15165.9121040724 3898.9437782805) (10 15158.2233031674 3884.0156108597) (10 15147.0588235294
3880.0904977376))
((0 . "LWPOLYLINE") (100 . "AcDbEntity") (8 . "PLANTS") (62 . 94) (370 . 13) (100 . "AcDbPolyline") (90 . 2) (70 . 0)
(43 . 0.0) (10 15188.5350678733 3736.8028280543) (10 15147.0588235294 3740.5727375566))
((0 . "LWPOLYLINE") (100 . "AcDbEntity") (8 . "PLANTS") (62 . 94) (370 . 13) (100 . "AcDbPolyline") (90 . 2) (70 . 0)
(43 . 0.0) (10 15158.371040724 3438.9140271493) (10 15147.0588235294 3408.7478506787))
((0 . "LWPOLYLINE") (100 . "AcDbEntity") (8 . "PLANTS") (62 . 94) (370 . 13) (100 . "AcDbPolyline") (90 . 2) (70 . 0)
(43 . 0.0) (10 15150.8299773756 3834.8416289593) (10 15188.5350678733 3834.8416289593))
((0 . "LWPOLYLINE") (100 . "AcDbEntity") (8 . "PLANTS") (62 . 94) (370 . 13) (100 . "AcDbPolyline") (90 . 2) (70 . 0)
(43 . 0.0) (10 15154.5998868778 4049.7737556561) (10 15169.6832579186 4072.3981900452))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15188.5350678733 3706.6360859729 0.0) (10 15183.7888084084 3688.4739400432 0.0) (10 15149.1918082712
3712.4696584686 0.0) (10 15158.371040724 3687.7828054299 0.0))
((0 . "LWPOLYLINE") (100 . "AcDbEntity") (8 . "PLANTS") (62 . 94) (370 . 13) (100 . "AcDbPolyline") (90 . 2) (70 . 0)
(43 . 0.0) (10 15162.1421945701 3785.8216063348) (10 15188.5350678733 3744.3438914027))
((0 . "LWPOLYLINE") (100 . "AcDbEntity") (8 . "PLANTS") (62 . 94) (370 . 13) (100 . "AcDbPolyline") (90 . 3) (70 . 0)
(43 . 0.0) (10 15196.0803167421 3827.3005656109) (10 15184.6175339367 3804.6823529412) (10 15162.1421945701
3785.8216063348))
((0 . "LWPOLYLINE") (100 . "AcDbEntity") (8 . "PLANTS") (62 . 94) (370 . 13) (100 . "AcDbPolyline") (90 . 2) (70 . 0)
(43 . 0.0) (10 15162.1421945701 414.782239819) (10 15169.6832579186 418.5520361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15165.9121040724 3898.9437782805 0.0) (10 15189.8515266335 3890.8711447033 0.0) (10 15212.864377765
3916.3305302232 0.0) (10 15211.1595022624 3940.4227375566 0.0))
((0 . "LWPOLYLINE") (100 . "AcDbEntity") (8 . "PLANTS") (62 . 94) (370 . 13) (100 . "AcDbPolyline") (90 . 2) (70 . 0)
(43 . 0.0) (10 15165.9121040724 3536.9535067873) (10 15165.9121040724 3514.3290723982))
((0 . "LWPOLYLINE") (100 . "AcDbEntity") (8 . "PLANTS") (62 . 94) (370 . 13) (100 . "AcDbPolyline") (90 . 3) (70 . 0)
(43 . 0.0) (10 15165.9121040724 3536.9535067873) (10 15182.0449095023 3570.735520362) (10 15188.5350678733
3574.6606334842))
((0 . "LWPOLYLINE") (100 . "AcDbEntity") (8 . "PLANTS") (62 . 94) (370 . 13) (100 . "AcDbPolyline") (90 . 2) (70 . 0)
(43 . 0.0) (10 15165.9121040724 3514.3290723982) (10 15203.6199095023 3506.7873303167))
((0 . "LWPOLYLINE") (100 . "AcDbEntity") (8 . "PLANTS") (62 . 94) (370 . 13) (100 . "AcDbPolyline") (90 . 3) (70 . 0)
(43 . 0.0) (10 15202.8645927602 4066.3650452489) (10 15192.4195701357 4072.1613122172) (10 15169.6832579186
4072.3981900452))
((0 . "LWPOLYLINE") (100 . "AcDbEntity") (8 . "PLANTS") (62 . 94) (370 . 13) (100 . "AcDbPolyline") (90 . 3) (70 . 0)
(43 . 0.0) (10 15169.6832579186 1036.9541855204) (10 15166.2075791855 1029.4048642534) (10 15169.6832579186
1010.5571266968))
((0 . "LWPOLYLINE") (100 . "AcDbEntity") (8 . "PLANTS") (62 . 94) (370 . 13) (100 . "AcDbPolyline") (90 . 2) (70 . 0)
(43 . 0.0) (10 15169.6832579186 1010.5571266968) (10 15192.3076923077 995.4751131222))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15169.6832579186 972.850678733 0.0) (10 15140.9479323077 977.2782761296 0.0) (10 15151.9545541709
1007.3897552179 0.0) (10 15169.6832579186 1010.5571266968 0.0))
((0 . "LWPOLYLINE") (100 . "AcDbEntity") (8 . "PLANTS") (62 . 94) (370 . 13) (100 . "AcDbPolyline") (90 . 2) (70 . 0)
(43 . 0.0) (10 15169.6832579186 972.850678733) (10 15184.7680995475 972.850678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15203.6199095023 384.6153846154 0.0) (10 15204.905173598 402.7798000265 0.0) (10 15178.2583930304
409.006688402 0.0) (10 15169.6832579186 418.5520361991 0.0))
((0 . "LWPOLYLINE") (100 . "AcDbEntity") (8 . "PLANTS") (62 . 94) (370 . 13) (100 . "AcDbPolyline") (90 . 3) (70 . 0)
(43 . 0.0) (10 15188.5350678733 3355.9580316742) (10 15181.1432126697 3337.1040723982) (10 15180.9954751131
3318.2501131222))
((0 . "LWPOLYLINE") (100 . "AcDbEntity") (8 . "PLANTS") (62 . 94) (370 . 13) (100 . "AcDbPolyline") (90 . 2) (70 . 0)
(43 . 0.0) (10 15184.7680995475 3442.6845022624) (10 15199.8472850679 3435.1435520362))
((0 . "LWPOLYLINE") (100 . "AcDbEntity") (8 . "PLANTS") (62 . 94) (370 . 13) (100 . "AcDbPolyline") (90 . 3) (70 . 0)
(43 . 0.0) (10 15184.7680995475 972.850678733) (10 15193.5035067873 942.6838235294) (10 15207.3925339367
931.3716063348))
((0 . "LWPOLYLINE") (100 . "AcDbEntity") (8 . "PLANTS") (62 . 94) (370 . 13) (100 . "AcDbPolyline") (90 . 2) (70 . 0)
(43 . 0.0) (10 15184.7680995475 972.850678733) (10 15192.3076923077 995.4751131222))
((0 . "LWPOLYLINE") (100 . "AcDbEntity") (8 . "PLANTS") (62 . 94) (370 . 13) (100 . "AcDbPolyline") (90 . 3) (70 . 0)
(43 . 0.0) (10 15196.0803167421 3827.3005656109) (10 15192.3076923077 3834.8416289593) (10 15188.5350678733
3834.8416289593))
((0 . "LWPOLYLINE") (100 . "AcDbEntity") (8 . "PLANTS") (62 . 94) (370 . 13) (100 . "AcDbPolyline") (90 . 2) (70 . 0)
(43 . 0.0) (10 15192.3076923077 3861.2372171946) (10 15188.5350678733 3834.8416289593))
((0 . "LWPOLYLINE") (100 . "AcDbEntity") (8 . "PLANTS") (62 . 94) (370 . 13) (100 . "AcDbPolyline") (90 . 2) (70 . 0)
(43 . 0.0) (10 15188.5350678733 3744.3438914027) (10 15188.5350678733 3736.8028280543))
((0 . "LWPOLYLINE") (100 . "AcDbEntity") (8 . "PLANTS") (62 . 94) (370 . 13) (100 . "AcDbPolyline") (90 . 3) (70 . 0)
(43 . 0.0) (10 15207.3925339367 3774.5093891403) (10 15198.7923076923 3755.6561085973) (10 15188.5350678733
3744.3438914027))
((0 . "LWPOLYLINE") (100 . "AcDbEntity") (8 . "PLANTS") (62 . 94) (370 . 13) (100 . "AcDbPolyline") (90 . 2) (70 . 0)
(43 . 0.0) (10 15188.5350678733 3736.8028280543) (10 15188.5350678733 3717.9483031674))
((0 . "LWPOLYLINE") (100 . "AcDbEntity") (8 . "PLANTS") (62 . 94) (370 . 13) (100 . "AcDbPolyline") (90 . 2) (70 . 0)
(43 . 0.0) (10 15248.8687782805 3717.9483031674) (10 15188.5350678733 3717.9483031674))
((0 . "LWPOLYLINE") (100 . "AcDbEntity") (8 . "PLANTS") (62 . 94) (370 . 13) (100 . "AcDbPolyline") (90 . 2) (70 . 0)
(43 . 0.0) (10 15188.5350678733 3706.6360859729) (10 15188.5350678733 3717.9483031674))
((0 . "LWPOLYLINE") (100 . "AcDbEntity") (8 . "PLANTS") (62 . 94) (370 . 13) (100 . "AcDbPolyline") (90 . 3) (70 . 0)
(43 . 0.0) (10 15192.3076923077 3661.3872171946) (10 15192.1599547511 3699.088800905) (10 15188.5350678733
3706.6360859729))
((0 . "LWPOLYLINE") (100 . "AcDbEntity") (8 . "PLANTS") (62 . 94) (370 . 13) (100 . "AcDbPolyline") (90 . 2) (70 . 0)
(43 . 0.0) (10 15188.5350678733 3585.9728506787) (10 15188.5350678733 3574.6606334842))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15192.3076923077 3661.3872171946 0.0) (10 15166.6672581942 3637.146185945 0.0) (10 15212.4072769582
3613.2217391386 0.0) (10 15188.5350678733 3585.9728506787 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15203.6199095023 3506.7873303168 0.0) (10 15218.7409693353 3526.7582326863 0.0) (10 15217.9305421309
3568.2110089557 0.0) (10 15188.5350678733 3574.6606334842 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15301.657239819 248.8687782805 0.0) (10 15272.8810899435 221.5091834279 0.0) (10 15223.1113215581
218.9790292899 0.0) (10 15188.5350678733 237.556561086 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15188.5350678733 237.556561086 0.0) (10 15185.14416869 267.8046345812 0.0) (10 15216.7475810461
280.4960270352 0.0) (10 15237.556561086 290.3478506787 0.0))
((0 . "LWPOLYLINE") (100 . "AcDbEntity") (8 . "PLANTS") (62 . 94) (370 . 13) (100 . "AcDbPolyline") (90 . 3) (70 . 0)
(43 . 0.0) (10 15192.3076923077 3661.3872171946) (10 15211.1554298643 3656.4125565611) (10 15218.7047511312
3642.5339366516))
((0 . "LWPOLYLINE") (100 . "AcDbEntity") (8 . "PLANTS") (62 . 94) (370 . 13) (100 . "AcDbPolyline") (90 . 3) (70 . 0)
(43 . 0.0) (10 15203.6199095023 3506.7873303167) (10 15202.4240950226 3484.1628959276) (10 15192.3076923077
3472.850678733))
((0 . "LWPOLYLINE") (100 . "AcDbEntity") (8 . "PLANTS") (62 . 94) (370 . 13) (100 . "AcDbPolyline") (90 . 3) (70 . 0)
(43 . 0.0) (10 15246.9852941176 1059.5786199095) (10 15211.1595022624 1063.1937782805) (10 15192.3076923077
1052.036199095))
((0 . "LWPOLYLINE") (100 . "AcDbEntity") (8 . "PLANTS") (62 . 94) (370 . 13) (100 . "AcDbPolyline") (90 . 3) (70 . 0)
(43 . 0.0) (10 15243.2126696833 999.2449095023) (10 15203.6199095023 999.0978506787) (10 15192.3076923077
995.4751131222))
((0 . "LWPOLYLINE") (100 . "AcDbEntity") (8 . "PLANTS") (62 . 94) (370 . 13) (100 . "AcDbPolyline") (90 . 2) (70 . 0)
(43 . 0.0) (10 15226.2443438914 3827.3005656109) (10 15196.0803167421 3827.3005656109))
((0 . "LWPOLYLINE") (100 . "AcDbEntity") (8 . "PLANTS") (62 . 94) (370 . 13) (100 . "AcDbPolyline") (90 . 2) (70 . 0)
(43 . 0.0) (10 15196.0803167421 3423.8313348416) (10 15199.8472850679 3435.1435520362))
((0 . "LWPOLYLINE") (100 . "AcDbEntity") (8 . "PLANTS") (62 . 94) (370 . 13) (100 . "AcDbPolyline") (90 . 2) (70 . 0)
(43 . 0.0) (10 15202.9091234073 4108.3129706299) (10 15202.8645927602 4066.3650452489))
((0 . "LWPOLYLINE") (100 . "AcDbEntity") (8 . "PLANTS") (62 . 94) (370 . 13) (100 . "AcDbPolyline") (90 . 2) (70 . 0)
(43 . 0.0) (10 15214.9321266968 3438.9140271493) (10 15199.8472850679 3435.1435520362))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6711848908) (40
. 1) (40 . 1) (40 . 1) (40 . 1) (10 15202.86459276 4066.365045249 0.0) (10 15184.9215028639 4043.2561890818 0.0) (10
15207.9128168684 3994.7776270671 0.0) (10 15202.5173848363 3953.2617565204 0.0) (10 15211.1595022624 3940.4227375566
0.0))
((0 . "LWPOLYLINE") (100 . "AcDbEntity") (8 . "PLANTS") (62 . 94) (370 . 13) (100 . "AcDbPolyline") (90 . 3) (70 . 0)
(43 . 0.0) (10 15248.8687782805 901.2075791855) (10 15218.7047511312 902.2632352941) (10 15203.6199095023
912.5197963801))
((0 . "LWPOLYLINE") (100 . "AcDbEntity") (8 . "PLANTS") (62 . 94) (370 . 13) (100 . "AcDbPolyline") (90 . 2) (70 . 0)
(43 . 0.0) (10 15203.6199095023 912.5197963801) (10 15207.3925339367 931.3716063348))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15237.556561086 309.1996606335 0.0) (10 15251.4753772875 336.200211954 0.0) (10 15229.5391777478
373.2117367827 0.0) (10 15203.6199095023 384.6153846154 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6727588435) (40
. 1) (40 . 1) (40 . 1) (40 . 1) (10 15237.556561086 309.1996606335 0.0) (10 15212.4903551522 303.1940950918 0.0) (10
15173.660084884 349.4372642186 0.0) (10 15188.1762114735 382.0285921955 0.0) (10 15203.6199095022 384.6153846154 0.0))
((0 . "LWPOLYLINE") (100 . "AcDbEntity") (8 . "PLANTS") (62 . 94) (370 . 13) (100 . "AcDbPolyline") (90 . 2) (70 . 0)
(43 . 0.0) (10 15245.0961538462 946.4564479638) (10 15207.3925339367 931.3716063348))
((0 . "LWPOLYLINE") (100 . "AcDbEntity") (8 . "PLANTS") (62 . 94) (370 . 13) (100 . "AcDbPolyline") (90 . 2) (70 . 0)
(43 . 0.0) (10 15245.0961538462 3944.1926470588) (10 15211.1595022624 3940.4227375566))
((0 . "LWPOLYLINE") (100 . "AcDbEntity") (8 . "PLANTS") (62 . 94) (370 . 13) (100 . "AcDbPolyline") (90 . 2) (70 . 0)
(43 . 0.0) (10 15218.7047511312 3876.3193438914) (10 15256.4083710407 3887.631561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15222.471719457 3631.221719457 0.0) (10 15239.747543351 3597.1543594166 0.0) (10 15224.7060578238
3554.9921195998 0.0) (10 15256.4083710407 3525.6412895928 0.0))
((0 . "LWPOLYLINE") (100 . "AcDbEntity") (8 . "PLANTS") (62 . 94) (370 . 13) (100 . "AcDbPolyline") (90 . 3) (70 . 0)
(43 . 0.0) (10 15230.0169683258 456.2584841629) (10 15228.8183257919 467.5658371041) (10 15222.471719457
475.1131221719))
((0 . "LWPOLYLINE") (100 . "AcDbEntity") (8 . "PLANTS") (62 . 94) (370 . 13) (100 . "AcDbPolyline") (90 . 3) (70 . 0)
(43 . 0.0) (10 15226.2443438914 3827.3005656109) (10 15234.8417420814 3808.446719457) (10 15248.8687782805
3797.1338235294))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15226.2443438914 3827.3005656109 0.0) (10 15246.2170168704 3862.9190924782 0.0) (10 15298.1730294053
3862.2418072632 0.0) (10 15331.8269230769 3868.778280543 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15275.2658371041 361.9909502263 0.0) (10 15280.536493188 394.4154862639 0.0) (10 15273.5706045389
453.7095818366 0.0) (10 15230.0169683258 456.2584841629 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15275.2658371041 361.9909502262 0.0) (10 15234.9539296908 365.0254167305 0.0) (10 15227.9816121834
433.1189070384 0.0) (10 15230.0169683258 456.2584841629 0.0))
((0 . "LWPOLYLINE") (100 . "AcDbEntity") (8 . "PLANTS") (62 . 94) (370 . 13) (100 . "AcDbPolyline") (90 . 2) (70 . 0)
(43 . 0.0) (10 15237.556561086 309.1996606335) (10 15237.556561086 290.3478506787))
((0 . "LWPOLYLINE") (100 . "AcDbEntity") (8 . "PLANTS") (62 . 94) (370 . 13) (100 . "AcDbPolyline") (90 . 3) (70 . 0)
(43 . 0.0) (10 15296.0011312217 282.8054298643) (10 15248.8687782805 282.9600678733) (10 15237.556561086
290.3478506787))
((0 . "LWPOLYLINE") (100 . "AcDbEntity") (8 . "PLANTS") (62 . 94) (370 . 13) (100 . "AcDbPolyline") (90 . 2) (70 . 0)
(43 . 0.0) (10 15243.2126696833 999.2449095023) (10 15279.0328054299 999.2449095023))
((0 . "LWPOLYLINE") (100 . "AcDbEntity") (8 . "PLANTS") (62 . 94) (370 . 13) (100 . "AcDbPolyline") (90 . 2) (70 . 0)
(43 . 0.0) (10 15243.2126696833 999.2449095023) (10 15245.0961538462 946.4564479638))
((0 . "LWPOLYLINE") (100 . "AcDbEntity") (8 . "PLANTS") (62 . 94) (370 . 13) (100 . "AcDbPolyline") (90 . 3) (70 . 0)
(43 . 0.0) (10 15243.2126696833 999.2449095023) (10 15248.721040724 1036.9541855204) (10 15246.9852941176
1059.5786199095))
((0 . "LWPOLYLINE") (100 . "AcDbEntity") (8 . "PLANTS") (62 . 94) (370 . 13) (100 . "AcDbPolyline") (90 . 2) (70 . 0)
(43 . 0.0) (10 15245.0961538462 4000.7537330317) (10 15256.4083710407 4004.5248868778))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15245.0961538462 3944.1926470588 0.0) (10 15258.604981154 3927.1722663302 0.0) (10 15282.5416615399
3927.9039894843 0.0) (10 15301.657239819 3930.9954751131 0.0))
((0 . "LWPOLYLINE") (100 . "AcDbEntity") (8 . "PLANTS") (62 . 94) (370 . 13) (100 . "AcDbPolyline") (90 . 2) (70 . 0)
(43 . 0.0) (10 15245.0961538462 3944.1926470588) (10 15256.4083710407 3966.817081448))
((0 . "LWPOLYLINE") (100 . "AcDbEntity") (8 . "PLANTS") (62 . 94) (370 . 13) (100 . "AcDbPolyline") (90 . 2) (70 . 0)
(43 . 0.0) (10 15252.6414027149 942.6838235294) (10 15245.0961538462 946.4564479638))
((0 . "LWPOLYLINE") (100 . "AcDbEntity") (8 . "PLANTS") (62 . 94) (370 . 13) (100 . "AcDbPolyline") (90 . 3) (70 . 0)
(43 . 0.0) (10 15241.3272624434 1104.2679319591) (10 15241.3272624434 1074.6606334842) (10 15246.9852941176
1059.5786199095))
((0 . "LWPOLYLINE") (100 . "AcDbEntity") (8 . "PLANTS") (62 . 94) (370 . 13) (100 . "AcDbPolyline") (90 . 2) (70 . 0)
(43 . 0.0) (10 15246.9852941176 1059.5786199095) (10 15297.8902714932 1063.3484162896))
((0 . "LWPOLYLINE") (100 . "AcDbEntity") (8 . "PLANTS") (62 . 94) (370 . 13) (100 . "AcDbPolyline") (90 . 2) (70 . 0)
(43 . 0.0) (10 15248.8687782805 3710.407239819) (10 15248.8687782805 3717.9483031674))
((0 . "LWPOLYLINE") (100 . "AcDbEntity") (8 . "PLANTS") (62 . 94) (370 . 13) (100 . "AcDbPolyline") (90 . 3) (70 . 0)
(43 . 0.0) (10 15252.6414027149 3759.4272624434) (10 15249.0165158371 3751.8787330317) (10 15248.8687782805
3717.9483031674))
((0 . "LWPOLYLINE") (100 . "AcDbEntity") (8 . "PLANTS") (62 . 94) (370 . 13) (100 . "AcDbPolyline") (90 . 3) (70 . 0)
(43 . 0.0) (10 15294.1176470588 3687.7828054299) (10 15286.4219457014 3709.2027149321) (10 15248.8687782805
3710.407239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15248.8687782805 3710.407239819 0.0) (10 15228.9459494825 3688.0148798055 0.0) (10 15244.8770317668
3643.0252934654 0.0) (10 15275.2658371041 3638.7627828054 0.0))
((0 . "LWPOLYLINE") (100 . "AcDbEntity") (8 . "PLANTS") (62 . 94) (370 . 13) (100 . "AcDbPolyline") (90 . 2) (70 . 0)
(43 . 0.0) (10 15252.6414027149 942.6838235294) (10 15248.8687782805 901.2075791855))
((0 . "LWPOLYLINE") (100 . "AcDbEntity") (8 . "PLANTS") (62 . 94) (370 . 13) (100 . "AcDbPolyline") (90 . 3) (70 . 0)
(43 . 0.0) (10 15248.8687782805 901.2075791855) (10 15294.1176470588 902.2632352941) (10 15318.6255656109
918.1759049774))
((0 . "LWPOLYLINE") (100 . "AcDbEntity") (8 . "PLANTS") (62 . 94) (370 . 13) (100 . "AcDbPolyline") (90 . 2) (70 . 0)
(43 . 0.0) (10 15252.6414027149 3518.0995475113) (10 15256.4083710407 3525.6412895928))
((0 . "LWPOLYLINE") (100 . "AcDbEntity") (8 . "PLANTS") (62 . 94) (370 . 13) (100 . "AcDbPolyline") (90 . 2) (70 . 0)
(43 . 0.0) (10 15252.6414027149 3374.811199095) (10 15256.4083710407 3393.665158371))
((0 . "LWPOLYLINE") (100 . "AcDbEntity") (8 . "PLANTS") (62 . 94) (370 . 13) (100 . "AcDbPolyline") (90 . 3) (70 . 0)
(43 . 0.0) (10 15252.6414027149 942.6838235294) (10 15293.9643665158 948.8729638009) (10 15318.6255656109
918.1759049774))
((0 . "LWPOLYLINE") (100 . "AcDbEntity") (8 . "PLANTS") (62 . 94) (370 . 13) (100 . "AcDbPolyline") (90 . 2) (70 . 0)
(43 . 0.0) (10 15256.4083710407 4004.5248868778) (10 15256.4083710407 3966.817081448))
((0 . "LWPOLYLINE") (100 . "AcDbEntity") (8 . "PLANTS") (62 . 94) (370 . 13) (100 . "AcDbPolyline") (90 . 2) (70 . 0)
(43 . 0.0) (10 15256.4083710407 4004.5248868778) (10 15260.1809954751 4015.8371040724))
((0 . "LWPOLYLINE") (100 . "AcDbEntity") (8 . "PLANTS") (62 . 94) (370 . 13) (100 . "AcDbPolyline") (90 . 2) (70 . 0)
(43 . 0.0) (10 15256.4083710407 3966.817081448) (10 15301.657239819 3974.3593891403))
((0 . "LWPOLYLINE") (100 . "AcDbEntity") (8 . "PLANTS") (62 . 94) (370 . 13) (100 . "AcDbPolyline") (90 . 2) (70 . 0)
(43 . 0.0) (10 15279.0328054299 3525.6412895928) (10 15256.4083710407 3525.6412895928))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15354.4513574661 4049.7737556561 0.0) (10 15301.3076664785 4084.1086807224 0.0) (10 15300.8589742661
4015.8458568024 0.0) (10 15260.1809954751 4015.8371040724 0.0))
((0 . "LWPOLYLINE") (100 . "AcDbEntity") (8 . "PLANTS") (62 . 94) (370 . 13) (100 . "AcDbPolyline") (90 . 2) (70 . 0)
(43 . 0.0) (10 15279.0328054299 3616.1390271493) (10 15275.2658371041 3638.7627828054))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15294.1176470588 3687.7828054299 0.0) (10 15273.7017946864 3676.1996164805 0.0) (10 15292.6348553238
3651.4462885517 0.0) (10 15275.2658371041 3638.7627828054 0.0))
((0 . "LWPOLYLINE") (100 . "AcDbEntity") (8 . "PLANTS") (62 . 94) (370 . 13) (100 . "AcDbPolyline") (90 . 3) (70 . 0)
(43 . 0.0) (10 15275.2658371041 361.9909502262) (10 15287.6330316742 335.596719457) (10 15297.8902714932
324.2845022624))
((0 . "LWPOLYLINE") (100 . "AcDbEntity") (8 . "PLANTS") (62 . 94) (370 . 13) (100 . "AcDbPolyline") (90 . 2) (70 . 0)
(43 . 0.0) (10 15279.0328054299 3616.1390271493) (10 15312.9694570136 3612.367760181))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6530141734) (40
. 1) (40 . 1) (40 . 1) (40 . 1) (10 15279.0328054299 3525.6412895928 0.0) (10 15291.8809515768 3549.1798240274 0.0) (10
15253.7613007422 3575.3837231407 0.0) (10 15266.695979501 3607.7453537325 0.0) (10 15279.0328054299 3616.1390271494
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15279.0328054299 3525.6412895928 0.0) (10 15293.7214480583 3511.5829569667 0.0) (10 15279.433825989
3489.9815345585 0.0) (10 15294.1176470588 3476.6211538462 0.0))
((0 . "LWPOLYLINE") (100 . "AcDbEntity") (8 . "PLANTS") (62 . 94) (370 . 13) (100 . "AcDbPolyline") (90 . 2) (70 . 0)
(43 . 0.0) (10 15282.8054298643 991.7053167421) (10 15279.0328054299 999.2449095023))
((0 . "LWPOLYLINE") (100 . "AcDbEntity") (8 . "PLANTS") (62 . 94) (370 . 13) (100 . "AcDbPolyline") (90 . 3) (70 . 0)
(43 . 0.0) (10 15305.4298642534 1021.8693438914) (10 15297.7397058824 1011.6073529412) (10 15279.0328054299
999.2449095023))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15282.8054298642 512.8195701357 0.0) (10 15297.5969353556 522.480043144 0.0) (10 15312.8967841777
485.5846145877 0.0) (10 15305.4298642534 478.882918552 0.0))
((0 . "LWPOLYLINE") (100 . "AcDbEntity") (8 . "PLANTS") (62 . 94) (370 . 13) (100 . "AcDbPolyline") (90 . 2) (70 . 0)
(43 . 0.0) (10 15305.4298642534 478.882918552) (10 15286.5780542986 475.1131221719))
((0 . "LWPOLYLINE") (100 . "AcDbEntity") (8 . "PLANTS") (62 . 94) (370 . 13) (100 . "AcDbPolyline") (90 . 3) (70 . 0)
(43 . 0.0) (10 15294.1176470588 3687.7828054299) (10 15320.5147058824 3688.8325791855) (10 15350.6787330317
3702.8661764706))
((0 . "LWPOLYLINE") (100 . "AcDbEntity") (8 . "PLANTS") (62 . 94) (370 . 13) (100 . "AcDbPolyline") (90 . 3) (70 . 0)
(43 . 0.0) (10 15296.0011312217 282.8054298643) (10 15301.5054298643 271.4932126697) (10 15301.657239819
248.8687782805))
((0 . "LWPOLYLINE") (100 . "AcDbEntity") (8 . "PLANTS") (62 . 94) (370 . 13) (100 . "AcDbPolyline") (90 . 2) (70 . 0)
(43 . 0.0) (10 15296.0011312217 282.8054298643) (10 15297.8902714932 324.2845022624))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15296.0011312217 282.8054298642 0.0) (10 15330.8279920214 261.663192091 0.0) (10 15339.1950349052
305.5354812287 0.0) (10 15365.7635746606 305.4298642534 0.0))
((0 . "LWPOLYLINE") (100 . "AcDbEntity") (8 . "PLANTS") (62 . 94) (370 . 13) (100 . "AcDbPolyline") (90 . 3) (70 . 0)
(43 . 0.0) (10 15319.7843411284 1137.9237126369) (10 15320.5147058824 1137.7070135747) (10 15331.8269230769
1123.6792986425))
((0 . "LWPOLYLINE") (100 . "AcDbEntity") (8 . "PLANTS") (62 . 94) (370 . 13) (100 . "AcDbPolyline") (90 . 2) (70 . 0)
(43 . 0.0) (10 15297.8888566379 1122.9949732115) (10 15297.8902714932 1063.3484162896))
((0 . "LWPOLYLINE") (100 . "AcDbEntity") (8 . "PLANTS") (62 . 94) (370 . 13) (100 . "AcDbPolyline") (90 . 3) (70 . 0)
(43 . 0.0) (10 15305.4298642534 1021.8693438914) (10 15305.2821266968 1040.7239819005) (10 15297.8902714932
1063.3484162896))
((0 . "LWPOLYLINE") (100 . "AcDbEntity") (8 . "PLANTS") (62 . 94) (370 . 13) (100 . "AcDbPolyline") (90 . 2) (70 . 0)
(43 . 0.0) (10 15316.742081448 335.596719457) (10 15297.8902714932 324.2845022624))
((0 . "LWPOLYLINE") (100 . "AcDbEntity") (8 . "PLANTS") (62 . 94) (370 . 13) (100 . "AcDbPolyline") (90 . 3) (70 . 0)
(43 . 0.0) (10 15301.657239819 3930.9954751131) (10 15305.4298642534 3951.7349547511) (10 15301.657239819
3974.3593891403))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15358.2183257919 4012.0659502262 0.0) (10 15332.5395371025 4018.9849566485 0.0) (10 15303.970727463
4001.3359560729 0.0) (10 15301.657239819 3974.3593891403 0.0))
((0 . "LWPOLYLINE") (100 . "AcDbEntity") (8 . "PLANTS") (62 . 94) (370 . 13) (100 . "AcDbPolyline") (90 . 3) (70 . 0)
(43 . 0.0) (10 15328.0542986425 3902.7149321267) (10 15316.8898190045 3910.2628959276) (10 15301.657239819
3930.9954751131))
((0 . "LWPOLYLINE") (100 . "AcDbEntity") (8 . "PLANTS") (62 . 94) (370 . 13) (100 . "AcDbPolyline") (90 . 2) (70 . 0)
(43 . 0.0) (10 15301.657239819 3930.9954751131) (10 15346.9061085973 3936.6515837104))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15301.657239819 248.8687782805 0.0) (10 15316.3272577173 227.6745231675 0.0) (10 15349.3609901297
232.4645501584 0.0) (10 15369.5305429864 237.556561086 0.0))
((0 . "LWPOLYLINE") (100 . "AcDbEntity") (8 . "PLANTS") (62 . 94) (370 . 13) (100 . "AcDbPolyline") (90 . 3) (70 . 0)
(43 . 0.0) (10 15305.4298642534 1021.8693438914) (10 15354.4429864253 1018.2472850679) (10 15361.9909502262
1021.8693438914))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15305.4298642534 478.882918552 0.0) (10 15320.434132602 444.4841113361 0.0) (10 15297.7562910365
402.1352125243 0.0) (10 15316.742081448 369.5333710407 0.0))
((0 . "LWPOLYLINE") (100 . "AcDbEntity") (8 . "PLANTS") (62 . 94) (370 . 13) (100 . "AcDbPolyline") (90 . 3) (70 . 0)
(43 . 0.0) (10 15312.9694570136 3612.367760181) (10 15320.5187782805 3602.2597285068) (10 15339.3665158371
3597.2850678733))
((0 . "LWPOLYLINE") (100 . "AcDbEntity") (8 . "PLANTS") (62 . 94) (370 . 13) (100 . "AcDbPolyline") (90 . 3) (70 . 0)
(43 . 0.0) (10 15312.9694570136 3612.367760181) (10 15324.2816742081 3622.4828054299) (10 15346.9061085973
3627.4505656109))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15316.742081448 3774.5093891403 0.0) (10 15317.7327090958 3746.6077498422 0.0) (10 15355.9654352571
3732.3405910245 0.0) (10 15350.6787330317 3702.8661764706 0.0))
((0 . "LWPOLYLINE") (100 . "AcDbEntity") (8 . "PLANTS") (62 . 94) (370 . 13) (100 . "AcDbPolyline") (90 . 2) (70 . 0)
(43 . 0.0) (10 15343.1391402715 369.5333710407) (10 15316.742081448 369.5333710407))
((0 . "LWPOLYLINE") (100 . "AcDbEntity") (8 . "PLANTS") (62 . 94) (370 . 13) (100 . "AcDbPolyline") (90 . 2) (70 . 0)
(43 . 0.0) (10 15316.742081448 335.596719457) (10 15316.742081448 369.5333710407))
((0 . "LWPOLYLINE") (100 . "AcDbEntity") (8 . "PLANTS") (62 . 94) (370 . 13) (100 . "AcDbPolyline") (90 . 3) (70 . 0)
(43 . 0.0) (10 15343.1391402715 350.6787330317) (10 15335.5898190045 340.5713800905) (10 15316.742081448 335.596719457))
((0 . "LWPOLYLINE") (100 . "AcDbEntity") (8 . "PLANTS") (62 . 94) (370 . 13) (100 . "AcDbPolyline") (90 . 3) (70 . 0)
(43 . 0.0) (10 15380.842760181 904.9773755656) (10 15335.5938914027 905.1320135747) (10 15318.6255656109
918.1759049774))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15318.6255656109 918.1759049774 0.0) (10 15319.9242430022 960.753292554 0.0) (10 15373.522203459
953.3409289133 0.0) (10 15380.842760181 987.9326923077 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15395.92760181 3812.2171945701 0.0) (10 15374.2123513703 3793.3963805055 0.0) (10 15343.7228603528
3814.4949449925 0.0) (10 15320.5147058824 3797.1338235294 0.0))
((0 . "LWPOLYLINE") (100 . "AcDbEntity") (8 . "PLANTS") (62 . 94) (370 . 13) (100 . "AcDbPolyline") (90 . 3) (70 . 0)
(43 . 0.0) (10 15365.7635746606 1112.367081448) (10 15339.5142533937 1111.1636877828) (10 15324.2816742081
1089.7426470588))
((0 . "LWPOLYLINE") (100 . "AcDbEntity") (8 . "PLANTS") (62 . 94) (370 . 13) (100 . "AcDbPolyline") (90 . 2) (70 . 0)
(43 . 0.0) (10 15328.0542986425 3902.7149321267) (10 15331.8269230769 3868.778280543))
((0 . "LWPOLYLINE") (100 . "AcDbEntity") (8 . "PLANTS") (62 . 94) (370 . 13) (100 . "AcDbPolyline") (90 . 3) (70 . 0)
(43 . 0.0) (10 15328.0542986425 3902.7149321267) (10 15338.1707013575 3914.0271493213) (10 15346.9061085973
3936.6515837104))
((0 . "LWPOLYLINE") (100 . "AcDbEntity") (8 . "PLANTS") (62 . 94) (370 . 13) (100 . "AcDbPolyline") (90 . 2) (70 . 0)
(43 . 0.0) (10 15331.8269230769 3868.778280543) (10 15354.4513574661 3865.0071266968))
((0 . "LWPOLYLINE") (100 . "AcDbEntity") (8 . "PLANTS") (62 . 94) (370 . 13) (100 . "AcDbPolyline") (90 . 3) (70 . 0)
(43 . 0.0) (10 15339.3665158371 3597.2850678733) (10 15340.5707013575 3578.4380090498) (10 15354.4513574661
3570.890158371))
((0 . "LWPOLYLINE") (100 . "AcDbEntity") (8 . "PLANTS") (62 . 94) (370 . 13) (100 . "AcDbPolyline") (90 . 2) (70 . 0)
(43 . 0.0) (10 15350.6787330317 3619.9095022624) (10 15339.3665158371 3597.2850678733))
((0 . "LWPOLYLINE") (100 . "AcDbEntity") (8 . "PLANTS") (62 . 94) (370 . 13) (100 . "AcDbPolyline") (90 . 2) (70 . 0)
(43 . 0.0) (10 15343.1391402715 369.5333710407) (10 15343.1391402715 414.782239819))
((0 . "LWPOLYLINE") (100 . "AcDbEntity") (8 . "PLANTS") (62 . 94) (370 . 13) (100 . "AcDbPolyline") (90 . 3) (70 . 0)
(43 . 0.0) (10 15350.6787330317 448.7188914027) (10 15343.285520362 429.8642533937) (10 15343.1391402715 414.782239819))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15403.4671945701 448.7188914027 0.0) (10 15372.2286472132 446.5036778943 0.0) (10 15384.3935201398
391.5436565306 0.0) (10 15343.1391402715 414.782239819 0.0))
((0 . "LWPOLYLINE") (100 . "AcDbEntity") (8 . "PLANTS") (62 . 94) (370 . 13) (100 . "AcDbPolyline") (90 . 2) (70 . 0)
(43 . 0.0) (10 15373.3031674208 369.5333710407) (10 15343.1391402715 369.5333710407))
((0 . "LWPOLYLINE") (100 . "AcDbEntity") (8 . "PLANTS") (62 . 94) (370 . 13) (100 . "AcDbPolyline") (90 . 2) (70 . 0)
(43 . 0.0) (10 15343.1391402715 350.6787330317) (10 15343.1391402715 369.5333710407))
((0 . "LWPOLYLINE") (100 . "AcDbEntity") (8 . "PLANTS") (62 . 94) (370 . 13) (100 . "AcDbPolyline") (90 . 2) (70 . 0)
(43 . 0.0) (10 15343.1391402715 350.6787330317) (10 15358.2183257919 350.6787330317))
((0 . "LWPOLYLINE") (100 . "AcDbEntity") (8 . "PLANTS") (62 . 94) (370 . 13) (100 . "AcDbPolyline") (90 . 3) (70 . 0)
(43 . 0.0) (10 15354.4513574661 3944.1926470588) (10 15350.6787330317 3944.1926470588) (10 15346.9061085973
3936.6515837104))
((0 . "LWPOLYLINE") (100 . "AcDbEntity") (8 . "PLANTS") (62 . 94) (370 . 13) (100 . "AcDbPolyline") (90 . 2) (70 . 0)
(43 . 0.0) (10 15350.6787330317 3619.9095022624) (10 15346.9061085973 3627.4505656109))
((0 . "LWPOLYLINE") (100 . "AcDbEntity") (8 . "PLANTS") (62 . 94) (370 . 13) (100 . "AcDbPolyline") (90 . 3) (70 . 0)
(43 . 0.0) (10 15365.7635746606 3695.3238687783) (10 15354.5977375566 3665.1583710407) (10 15346.9061085973
3627.4505656109))
((0 . "LWPOLYLINE") (100 . "AcDbEntity") (8 . "PLANTS") (62 . 94) (370 . 13) (100 . "AcDbPolyline") (90 . 2) (70 . 0)
(43 . 0.0) (10 15365.7635746606 3695.3238687783) (10 15350.6787330317 3702.8661764706))
((0 . "LWPOLYLINE") (100 . "AcDbEntity") (8 . "PLANTS") (62 . 94) (370 . 13) (100 . "AcDbPolyline") (90 . 3) (70 . 0)
(43 . 0.0) (10 15350.6787330317 3619.9095022624) (10 15369.5305429864 3620.9661764706) (10 15369.9075423229
3621.2032458027))
((0 . "LWPOLYLINE") (100 . "AcDbEntity") (8 . "PLANTS") (62 . 94) (370 . 13) (100 . "AcDbPolyline") (90 . 2) (70 . 0)
(43 . 0.0) (10 15354.4513574661 4049.7737556561) (10 15358.2183257919 4038.4615384615))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15354.4513574661 4049.7737556561 0.0) (10 15320.5662397185 4116.320695684 0.0) (10 15390.3657120218
4166.3145012537 0.0) (10 15361.9846145134 4231.9546551368 0.0))
((0 . "LWPOLYLINE") (100 . "AcDbEntity") (8 . "PLANTS") (62 . 94) (370 . 13) (100 . "AcDbPolyline") (90 . 2) (70 . 0)
(43 . 0.0) (10 15354.4513574661 3944.1926470588) (10 15369.5305429864 3940.4227375566))
((0 . "LWPOLYLINE") (100 . "AcDbEntity") (8 . "PLANTS") (62 . 94) (370 . 13) (100 . "AcDbPolyline") (90 . 3) (70 . 0)
(43 . 0.0) (10 15361.9909502262 3993.2126696833) (10 15354.5977375566 3970.5882352941) (10 15354.4513574661
3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15354.4513574661 3865.0071266968 0.0) (10 15353.349057351 3835.0349749033 0.0) (10 15386.9682336414
3841.8120577667 0.0) (10 15395.92760181 3819.7582579186 0.0))
((0 . "LWPOLYLINE") (100 . "AcDbEntity") (8 . "PLANTS") (62 . 94) (370 . 13) (100 . "AcDbPolyline") (90 . 2) (70 . 0)
(43 . 0.0) (10 15354.4513574661 3865.0071266968) (10 15377.0757918552 3880.0904977376))
((0 . "LWPOLYLINE") (100 . "AcDbEntity") (8 . "PLANTS") (62 . 94) (370 . 13) (100 . "AcDbPolyline") (90 . 3) (70 . 0)
(43 . 0.0) (10 15360.3972656951 3543.1188692791) (10 15355.4980769231 3552.036199095) (10 15354.4513574661
3570.890158371))
((0 . "LWPOLYLINE") (100 . "AcDbEntity") (8 . "PLANTS") (62 . 94) (370 . 13) (100 . "AcDbPolyline") (90 . 2) (70 . 0)
(43 . 0.0) (10 15363.944840272 3572.2463237001) (10 15354.4513574661 3570.890158371))
((0 . "LWPOLYLINE") (100 . "AcDbEntity") (8 . "PLANTS") (62 . 94) (370 . 13) (100 . "AcDbPolyline") (90 . 2) (70 . 0)
(43 . 0.0) (10 15361.9909502262 1063.3484162896) (10 15354.4513574661 1070.8908371041))
((0 . "LWPOLYLINE") (100 . "AcDbEntity") (8 . "PLANTS") (62 . 94) (370 . 13) (100 . "AcDbPolyline") (90 . 2) (70 . 0)
(43 . 0.0) (10 15358.2183257919 4038.4615384615) (10 15358.2183257919 4012.0659502262))
((0 . "LWPOLYLINE") (100 . "AcDbEntity") (8 . "PLANTS") (62 . 94) (370 . 13) (100 . "AcDbPolyline") (90 . 3) (70 . 0)
(43 . 0.0) (10 15426.0916289593 4015.8371040724) (10 15403.4631221719 4041.0279411765) (10 15358.2183257919
4038.4615384615))
((0 . "LWPOLYLINE") (100 . "AcDbEntity") (8 . "PLANTS") (62 . 94) (370 . 13) (100 . "AcDbPolyline") (90 . 2) (70 . 0)
(43 . 0.0) (10 15361.9909502262 3993.2126696833) (10 15358.2183257919 4012.0659502262))
((0 . "LWPOLYLINE") (100 . "AcDbEntity") (8 . "PLANTS") (62 . 94) (370 . 13) (100 . "AcDbPolyline") (90 . 2) (70 . 0)
(43 . 0.0) (10 15361.9909502262 3993.2126696833) (10 15426.0916289593 3996.9838235294))
((0 . "LWPOLYLINE") (100 . "AcDbEntity") (8 . "PLANTS") (62 . 94) (370 . 13) (100 . "AcDbPolyline") (90 . 2) (70 . 0)
(43 . 0.0) (10 15361.9909502262 1063.3484162896) (10 15361.9909502262 1021.8693438914))
((0 . "LWPOLYLINE") (100 . "AcDbEntity") (8 . "PLANTS") (62 . 94) (370 . 13) (100 . "AcDbPolyline") (90 . 2) (70 . 0)
(43 . 0.0) (10 15361.9909502262 1063.3484162896) (10 15380.842760181 1074.6606334842))
((0 . "LWPOLYLINE") (100 . "AcDbEntity") (8 . "PLANTS") (62 . 94) (370 . 13) (100 . "AcDbPolyline") (90 . 2) (70 . 0)
(43 . 0.0) (10 15380.842760181 987.9326923077) (10 15361.9909502262 1021.8693438914))
((0 . "LWPOLYLINE") (100 . "AcDbEntity") (8 . "PLANTS") (62 . 94) (370 . 13) (100 . "AcDbPolyline") (90 . 3) (70 . 0)
(43 . 0.0) (10 15381.054331644 3712.72425286) (10 15379.7877828054 3710.407239819) (10 15365.7635746606
3695.3238687783))
((0 . "LWPOLYLINE") (100 . "AcDbEntity") (8 . "PLANTS") (62 . 94) (370 . 13) (100 . "AcDbPolyline") (90 . 3) (70 . 0)
(43 . 0.0) (10 15365.7635746606 1112.367081448) (10 15369.6866515837 1101.0624434389) (10 15380.842760181
1093.5152714932))
((0 . "LWPOLYLINE") (100 . "AcDbEntity") (8 . "PLANTS") (62 . 94) (370 . 13) (100 . "AcDbPolyline") (90 . 3) (70 . 0)
(43 . 0.0) (10 15365.7635746606 1112.367081448) (10 15365.9099547511 1161.3885746606) (10 15368.2018210804
1170.935630786))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15452.4886877828 279.0356334842 0.0) (10 15414.2139720736 265.0302900824 0.0) (10 15398.1387641771
304.8251647895 0.0) (10 15365.7635746606 305.4298642534 0.0))
((0 . "LWPOLYLINE") (100 . "AcDbEntity") (8 . "PLANTS") (62 . 94) (370 . 13) (100 . "AcDbPolyline") (90 . 3) (70 . 0)
(43 . 0.0) (10 15369.5305429864 320.5118778281) (10 15365.7635746606 316.742081448) (10 15365.7635746606
305.4298642534))
((0 . "LWPOLYLINE") (100 . "AcDbEntity") (8 . "PLANTS") (62 . 94) (370 . 13) (100 . "AcDbPolyline") (90 . 2) (70 . 0)
(43 . 0.0) (10 15411.0124434389 1172.7007918552) (10 15375.5212676634 1175.9261625471))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15369.5305429864 237.556561086 0.0) (10 15396.1593206686 229.14584306 0.0) (10 15425.7836889869
229.639208489 0.0) (10 15452.4886877828 237.556561086 0.0))
((0 . "LWPOLYLINE") (100 . "AcDbEntity") (8 . "PLANTS") (62 . 94) (370 . 13) (100 . "AcDbPolyline") (90 . 2) (70 . 0)
(43 . 0.0) (10 15369.5305429864 237.556561086) (10 15373.3031674208 263.9507918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15373.3031674208 369.5333710407 0.0) (10 15358.4786995158 313.0474418664 0.0) (10 15458.8923613986
343.8175190528 0.0) (10 15463.8009049774 290.3478506787 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15373.3031674208 369.5333710407 0.0) (10 15391.8524325148 381.5482110045 0.0) (10 15419.1875227416
372.4412980151 0.0) (10 15433.6368778281 358.2211538462 0.0))
((0 . "LWPOLYLINE") (100 . "AcDbEntity") (8 . "PLANTS") (62 . 94) (370 . 13) (100 . "AcDbPolyline") (90 . 2) (70 . 0)
(43 . 0.0) (10 15380.842760181 1093.5152714932) (10 15380.842760181 1074.6606334842))
((0 . "LWPOLYLINE") (100 . "AcDbEntity") (8 . "PLANTS") (62 . 94) (370 . 13) (100 . "AcDbPolyline") (90 . 3) (70 . 0)
(43 . 0.0) (10 15380.842760181 1093.5152714932) (10 15411.0124434389 1107.5478506787) (10 15452.4886877828
1116.1397058824))
((0 . "LWPOLYLINE") (100 . "AcDbEntity") (8 . "PLANTS") (62 . 94) (370 . 13) (100 . "AcDbPolyline") (90 . 3) (70 . 0)
(43 . 0.0) (10 15429.8642533937 1033.181561086) (10 15418.5520361991 1048.1179864253) (10 15380.842760181
1074.6606334842))
((0 . "LWPOLYLINE") (100 . "AcDbEntity") (8 . "PLANTS") (62 . 94) (370 . 13) (100 . "AcDbPolyline") (90 . 2) (70 . 0)
(43 . 0.0) (10 15422.3246606335 1003.0175339367) (10 15380.842760181 987.9326923077))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15380.842760181 904.9773755656 0.0) (10 15405.2849801255 891.3230945932 0.0) (10 15435.0324460062
896.523731629 0.0) (10 15460.028280543 904.9773755656 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15380.842760181 904.9773755656 0.0) (10 15382.7473072941 934.755263691 0.0) (10 15413.1965757473
945.6897216793 0.0) (10 15437.4038461538 950.2262443439 0.0))
((0 . "LWPOLYLINE") (100 . "AcDbEntity") (8 . "PLANTS") (62 . 94) (370 . 13) (100 . "AcDbPolyline") (90 . 3) (70 . 0)
(43 . 0.0) (10 15399.7002262443 3914.0271493213) (10 15394.7373303167 3925.1847285068) (10 15388.3880090498
3929.110520362))
((0 . "LWPOLYLINE") (100 . "AcDbEntity") (8 . "PLANTS") (62 . 94) (370 . 13) (100 . "AcDbPolyline") (90 . 2) (70 . 0)
(43 . 0.0) (10 15422.3246606335 3733.0316742081) (10 15392.1549773756 3733.0316742081))
((0 . "LWPOLYLINE") (100 . "AcDbEntity") (8 . "PLANTS") (62 . 94) (370 . 13) (100 . "AcDbPolyline") (90 . 3) (70 . 0)
(43 . 0.0) (10 15403.4671945701 3808.446040724) (10 15392.3041855204 3770.739479638) (10 15392.1549773756
3733.0316742081))
((0 . "LWPOLYLINE") (100 . "AcDbEntity") (8 . "PLANTS") (62 . 94) (370 . 13) (100 . "AcDbPolyline") (90 . 2) (70 . 0)
(43 . 0.0) (10 15395.92760181 3812.2171945701) (10 15395.92760181 3819.7582579186))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4895106104) (40
. 1) (40 . 1) (40 . 1) (40 . 1) (10 15437.4038461539 3902.7149321267 0.0) (10 15438.3278421796 3885.8016722373 0.0) (10
15418.9993162129 3861.010875799 0.0) (10 15408.4378627661 3830.5838835801 0.0) (10 15395.92760181 3819.7582579185 0.0))
((0 . "LWPOLYLINE") (100 . "AcDbEntity") (8 . "PLANTS") (62 . 94) (370 . 13) (100 . "AcDbPolyline") (90 . 2) (70 . 0)
(43 . 0.0) (10 15403.4671945701 3808.446040724) (10 15395.92760181 3812.2171945701))
((0 . "LWPOLYLINE") (100 . "AcDbEntity") (8 . "PLANTS") (62 . 94) (370 . 13) (100 . "AcDbPolyline") (90 . 2) (70 . 0)
(43 . 0.0) (10 15414.7794117647 3947.963800905) (10 15403.4671945701 3947.963800905))
((0 . "LWPOLYLINE") (100 . "AcDbEntity") (8 . "PLANTS") (62 . 94) (370 . 13) (100 . "AcDbPolyline") (90 . 3) (70 . 0)
(43 . 0.0) (10 15403.4671945701 3808.446040724) (10 15422.3246606335 3812.0691176471) (10 15490.1979638009
3812.2171945701))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15403.4671945701 448.7188914027 0.0) (10 15476.0680715959 422.4414577107 0.0) (10 15440.5850842791
347.52222028 0.0) (10 15478.8857466063 305.4298642534 0.0))
((0 . "LWPOLYLINE") (100 . "AcDbEntity") (8 . "PLANTS") (62 . 94) (370 . 13) (100 . "AcDbPolyline") (90 . 2) (70 . 0)
(43 . 0.0) (10 15403.4671945701 448.7188914027) (10 15407.2398190045 460.0311085973))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15407.2398190045 4102.5636877828 0.0) (10 15401.1618211921 4072.1534083501 0.0) (10 15449.9811349682
4063.7678972721 0.0) (10 15444.9490950226 4030.9204751131 0.0))
((0 . "LWPOLYLINE") (100 . "AcDbEntity") (8 . "PLANTS") (62 . 94) (370 . 13) (100 . "AcDbPolyline") (90 . 3) (70 . 0)
(43 . 0.0) (10 15437.4038461538 1157.6159502262) (10 15414.935520362 1162.5857466063) (10 15411.0124434389
1172.7007918552))
((0 . "LWPOLYLINE") (100 . "AcDbEntity") (8 . "PLANTS") (62 . 94) (370 . 13) (100 . "AcDbPolyline") (90 . 3) (70 . 0)
(43 . 0.0) (10 15411.0124434389 1172.7007918552) (10 15411.010520362 1199.0950226244) (10 15426.0728006382
1210.3931168482))
((0 . "LWPOLYLINE") (100 . "AcDbEntity") (8 . "PLANTS") (62 . 94) (370 . 13) (100 . "AcDbPolyline") (90 . 2) (70 . 0)
(43 . 0.0) (10 15414.7794117647 3947.963800905) (10 15433.6368778281 3947.963800905))
((0 . "LWPOLYLINE") (100 . "AcDbEntity") (8 . "PLANTS") (62 . 94) (370 . 13) (100 . "AcDbPolyline") (90 . 3) (70 . 0)
(43 . 0.0) (10 15414.7794117647 3947.963800905) (10 15415.8372171946 3978.1292986425) (10 15426.0916289593
3989.4415158371))
((0 . "LWPOLYLINE") (100 . "AcDbEntity") (8 . "PLANTS") (62 . 94) (370 . 13) (100 . "AcDbPolyline") (90 . 3) (70 . 0)
(43 . 0.0) (10 15486.4253393665 3774.5093891403) (10 15463.8009049774 3752.9416289593) (10 15422.3246606335
3733.0316742081))
((0 . "LWPOLYLINE") (100 . "AcDbEntity") (8 . "PLANTS") (62 . 94) (370 . 13) (100 . "AcDbPolyline") (90 . 2) (70 . 0)
(43 . 0.0) (10 15422.3246606335 1003.0175339367) (10 15429.8642533937 1033.181561086))
((0 . "LWPOLYLINE") (100 . "AcDbEntity") (8 . "PLANTS") (62 . 94) (370 . 13) (100 . "AcDbPolyline") (90 . 3) (70 . 0)
(43 . 0.0) (10 15448.7160633484 1018.0995475113) (10 15441.0287330317 1007.9852941176) (10 15422.3246606335
1003.0175339367))
((0 . "LWPOLYLINE") (100 . "AcDbEntity") (8 . "PLANTS") (62 . 94) (370 . 13) (100 . "AcDbPolyline") (90 . 2) (70 . 0)
(43 . 0.0) (10 15422.3246606335 524.1317873303) (10 15433.6368778281 531.6742081448))
((0 . "LWPOLYLINE") (100 . "AcDbEntity") (8 . "PLANTS") (62 . 94) (370 . 13) (100 . "AcDbPolyline") (90 . 2) (70 . 0)
(43 . 0.0) (10 15426.0916289593 4015.8371040724) (10 15426.0916289593 3996.9838235294))
((0 . "LWPOLYLINE") (100 . "AcDbEntity") (8 . "PLANTS") (62 . 94) (370 . 13) (100 . "AcDbPolyline") (90 . 3) (70 . 0)
(43 . 0.0) (10 15444.9490950226 4030.9204751131) (10 15437.3997737557 4019.7622171946) (10 15426.0916289593
4015.8371040724))
((0 . "LWPOLYLINE") (100 . "AcDbEntity") (8 . "PLANTS") (62 . 94) (370 . 13) (100 . "AcDbPolyline") (90 . 2) (70 . 0)
(43 . 0.0) (10 15426.0916289593 3989.4415158371) (10 15426.0916289593 3996.9838235294))
((0 . "LWPOLYLINE") (100 . "AcDbEntity") (8 . "PLANTS") (62 . 94) (370 . 13) (100 . "AcDbPolyline") (90 . 3) (70 . 0)
(43 . 0.0) (10 15441.1764705882 3947.963800905) (10 15439.9722850679 3974.3593891403) (10 15426.0916289593
3989.4415158371))
((0 . "LWPOLYLINE") (100 . "AcDbEntity") (8 . "PLANTS") (62 . 94) (370 . 13) (100 . "AcDbPolyline") (90 . 3) (70 . 0)
(43 . 0.0) (10 15437.4038461538 1157.6159502262) (10 15437.2505656109 1195.3252262443) (10 15426.0922611471
1210.4063853769))
((0 . "LWPOLYLINE") (100 . "AcDbEntity") (8 . "PLANTS") (62 . 94) (370 . 13) (100 . "AcDbPolyline") (90 . 3) (70 . 0)
(43 . 0.0) (10 15448.7160633484 1018.0995475113) (10 15441.0287330317 1029.2571266968) (10 15429.8642533937
1033.181561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15471.3404977376 4068.6270361991 0.0) (10 15419.5706969488 4127.724625506 0.0) (10 15416.1270103372
4219.7274399924 0.0) (10 15433.640504066 4292.2964568653 0.0))
((0 . "LWPOLYLINE") (100 . "AcDbEntity") (8 . "PLANTS") (62 . 94) (370 . 13) (100 . "AcDbPolyline") (90 . 2) (70 . 0)
(43 . 0.0) (10 15441.1764705882 3947.963800905) (10 15433.6368778281 3947.963800905))
((0 . "LWPOLYLINE") (100 . "AcDbEntity") (8 . "PLANTS") (62 . 94) (370 . 13) (100 . "AcDbPolyline") (90 . 3) (70 . 0)
(43 . 0.0) (10 15437.4038461538 3902.7149321267) (10 15433.7832579186 3914.0271493213) (10 15433.6368778281
3947.963800905))
((0 . "LWPOLYLINE") (100 . "AcDbEntity") (8 . "PLANTS") (62 . 94) (370 . 13) (100 . "AcDbPolyline") (90 . 2) (70 . 0)
(43 . 0.0) (10 15433.6368778281 538.3579288359) (10 15433.6368778281 531.6742081448))
((0 . "LWPOLYLINE") (100 . "AcDbEntity") (8 . "PLANTS") (62 . 94) (370 . 13) (100 . "AcDbPolyline") (90 . 2) (70 . 0)
(43 . 0.0) (10 15452.4886877828 527.9044117647) (10 15433.6368778281 531.6742081448))
((0 . "LWPOLYLINE") (100 . "AcDbEntity") (8 . "PLANTS") (62 . 94) (370 . 13) (100 . "AcDbPolyline") (90 . 2) (70 . 0)
(43 . 0.0) (10 15437.4038461538 3902.7149321267) (10 15460.028280543 3902.7149321267))
((0 . "LWPOLYLINE") (100 . "AcDbEntity") (8 . "PLANTS") (62 . 94) (370 . 13) (100 . "AcDbPolyline") (90 . 2) (70 . 0)
(43 . 0.0) (10 15452.4886877828 1127.4519230769) (10 15437.4038461538 1157.6159502262))
((0 . "LWPOLYLINE") (100 . "AcDbEntity") (8 . "PLANTS") (62 . 94) (370 . 13) (100 . "AcDbPolyline") (90 . 2) (70 . 0)
(43 . 0.0) (10 15460.028280543 912.5197963801) (10 15437.4038461538 950.2262443439))
((0 . "LWPOLYLINE") (100 . "AcDbEntity") (8 . "PLANTS") (62 . 94) (370 . 13) (100 . "AcDbPolyline") (90 . 2) (70 . 0)
(43 . 0.0) (10 15444.9490950226 965.3082579186) (10 15437.4038461538 950.2262443439))
((0 . "LWPOLYLINE") (100 . "AcDbEntity") (8 . "PLANTS") (62 . 94) (370 . 13) (100 . "AcDbPolyline") (90 . 2) (70 . 0)
(43 . 0.0) (10 15441.1764705882 3947.963800905) (10 15478.8857466063 3947.963800905))
((0 . "LWPOLYLINE") (100 . "AcDbEntity") (8 . "PLANTS") (62 . 94) (370 . 13) (100 . "AcDbPolyline") (90 . 2) (70 . 0)
(43 . 0.0) (10 15444.9490950226 4030.9204751131) (10 15493.9649321267 4015.8371040724))
((0 . "LWPOLYLINE") (100 . "AcDbEntity") (8 . "PLANTS") (62 . 94) (370 . 13) (100 . "AcDbPolyline") (90 . 2) (70 . 0)
(43 . 0.0) (10 15448.7160633484 1018.0995475113) (10 15516.5893665158 1018.0995475113))
((0 . "LWPOLYLINE") (100 . "AcDbEntity") (8 . "PLANTS") (62 . 94) (370 . 13) (100 . "AcDbPolyline") (90 . 2) (70 . 0)
(43 . 0.0) (10 15452.4886877828 1127.4519230769) (10 15452.4886877828 1116.1397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15492.0814479638 1191.55260181 0.0) (10 15503.0230710979 1164.4793122106 0.0) (10 15489.5552103146
1125.309548343 0.0) (10 15452.4886877828 1127.4519230769 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15516.5893665158 1036.9541855204 0.0) (10 15488.1554181797 1056.9907601977 0.0) (10 15472.9545751449
1091.6860225234 0.0) (10 15452.4886877829 1116.1397058824 0.0))
((0 . "LWPOLYLINE") (100 . "AcDbEntity") (8 . "PLANTS") (62 . 94) (370 . 13) (100 . "AcDbPolyline") (90 . 2) (70 . 0)
(43 . 0.0) (10 15452.4886877828 279.0356334842) (10 15452.4886877828 237.556561086))
((0 . "LWPOLYLINE") (100 . "AcDbEntity") (8 . "PLANTS") (62 . 94) (370 . 13) (100 . "AcDbPolyline") (90 . 2) (70 . 0)
(43 . 0.0) (10 15452.4886877828 279.0356334842) (10 15463.8009049774 290.3478506787))
((0 . "LWPOLYLINE") (100 . "AcDbEntity") (8 . "PLANTS") (62 . 94) (370 . 13) (100 . "AcDbPolyline") (90 . 3) (70 . 0)
(43 . 0.0) (10 15505.2771493213 248.8687782805) (10 15486.4253393665 237.711199095) (10 15452.4886877828 237.556561086))
((0 . "LWPOLYLINE") (100 . "AcDbEntity") (8 . "PLANTS") (62 . 94) (370 . 13) (100 . "AcDbPolyline") (90 . 2) (70 . 0)
(43 . 0.0) (10 15475.1131221719 3891.4027149321) (10 15460.028280543 3902.7149321267))
((0 . "LWPOLYLINE") (100 . "AcDbEntity") (8 . "PLANTS") (62 . 94) (370 . 13) (100 . "AcDbPolyline") (90 . 3) (70 . 0)
(43 . 0.0) (10 15478.8857466063 3936.6515837104) (10 15472.3914027149 3932.7264705882) (10 15460.028280543
3902.7149321267))
((0 . "LWPOLYLINE") (100 . "AcDbEntity") (8 . "PLANTS") (62 . 94) (370 . 13) (100 . "AcDbPolyline") (90 . 2) (70 . 0)
(43 . 0.0) (10 15460.028280543 912.5197963801) (10 15460.028280543 904.9773755656))
((0 . "LWPOLYLINE") (100 . "AcDbEntity") (8 . "PLANTS") (62 . 94) (370 . 13) (100 . "AcDbPolyline") (90 . 2) (70 . 0)
(43 . 0.0) (10 15460.028280543 912.5197963801) (10 15482.6527149321 938.9140271493))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15460.028280543 904.9773755656 0.0) (10 15477.8927290297 897.6550137 0.0) (10 15500.5593718233
896.4829315203 0.0) (10 15516.5893665158 908.7471719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15482.6527149321 938.9140271493 0.0) (10 15493.1489012366 956.7270221022 0.0) (10 15474.6715875367
973.2482423952 0.0) (10 15463.8009049774 984.1628959276 0.0))
((0 . "LWPOLYLINE") (100 . "AcDbEntity") (8 . "PLANTS") (62 . 94) (370 . 13) (100 . "AcDbPolyline") (90 . 2) (70 . 0)
(43 . 0.0) (10 15463.8009049774 290.3478506787) (10 15478.8857466063 290.3478506787))
((0 . "LWPOLYLINE") (100 . "AcDbEntity") (8 . "PLANTS") (62 . 94) (370 . 13) (100 . "AcDbPolyline") (90 . 3) (70 . 0)
(43 . 0.0) (10 15467.5735294118 3861.2372171946) (10 15474.959841629 3872.5494343891) (10 15475.1131221719
3891.4027149321))
((0 . "LWPOLYLINE") (100 . "AcDbEntity") (8 . "PLANTS") (62 . 94) (370 . 13) (100 . "AcDbPolyline") (90 . 2) (70 . 0)
(43 . 0.0) (10 15497.7375565611 3898.9437782805) (10 15475.1131221719 3891.4027149321))
((0 . "LWPOLYLINE") (100 . "AcDbEntity") (8 . "PLANTS") (62 . 94) (370 . 13) (100 . "AcDbPolyline") (90 . 2) (70 . 0)
(43 . 0.0) (10 15478.8857466063 3936.6515837104) (10 15478.8857466063 3947.963800905))
((0 . "LWPOLYLINE") (100 . "AcDbEntity") (8 . "PLANTS") (62 . 94) (370 . 13) (100 . "AcDbPolyline") (90 . 3) (70 . 0)
(43 . 0.0) (10 15478.8857466063 3947.963800905) (10 15482.8019230769 3985.6716063348) (10 15493.9649321267
4015.8371040724))
((0 . "LWPOLYLINE") (100 . "AcDbEntity") (8 . "PLANTS") (62 . 94) (370 . 13) (100 . "AcDbPolyline") (90 . 2) (70 . 0)
(43 . 0.0) (10 15478.8857466063 3947.963800905) (10 15524.1346153846 3951.7349547511))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15478.8857466063 3936.6515837104 0.0) (10 15496.2605438574 3934.0782790375 0.0) (10 15482.821579973
3912.6708194385 0.0) (10 15497.7375565611 3910.2559954751 0.0))
((0 . "LWPOLYLINE") (100 . "AcDbEntity") (8 . "PLANTS") (62 . 94) (370 . 13) (100 . "AcDbPolyline") (90 . 3) (70 . 0)
(43 . 0.0) (10 15526.0180995475 3618.0238687783) (10 15501.5101809955 3649.0188914027) (10 15494.1258411378
3650.5944510764))
((0 . "LWPOLYLINE") (100 . "AcDbEntity") (8 . "PLANTS") (62 . 94) (370 . 13) (100 . "AcDbPolyline") (90 . 2) (70 . 0)
(43 . 0.0) (10 15526.0180995475 3618.0238687783) (10 15497.8403331169 3612.3882478628))
((0 . "LWPOLYLINE") (100 . "AcDbEntity") (8 . "PLANTS") (62 . 94) (370 . 13) (100 . "AcDbPolyline") (90 . 2) (70 . 0)
(43 . 0.0) (10 15478.8857466063 290.3478506787) (10 15478.8857466063 305.4298642534))
((0 . "LWPOLYLINE") (100 . "AcDbEntity") (8 . "PLANTS") (62 . 94) (370 . 13) (100 . "AcDbPolyline") (90 . 3) (70 . 0)
(43 . 0.0) (10 15516.5893665158 354.4485294118) (10 15497.5842760181 324.2845022624) (10 15478.8857466063
305.4298642534))
((0 . "LWPOLYLINE") (100 . "AcDbEntity") (8 . "PLANTS") (62 . 94) (370 . 13) (100 . "AcDbPolyline") (90 . 2) (70 . 0)
(43 . 0.0) (10 15505.2771493213 263.9507918552) (10 15478.8857466063 290.3478506787))
((0 . "LWPOLYLINE") (100 . "AcDbEntity") (8 . "PLANTS") (62 . 94) (370 . 13) (100 . "AcDbPolyline") (90 . 2) (70 . 0)
(43 . 0.0) (10 15492.0814479638 1191.55260181) (10 15482.6527149321 1187.7828054299))
((0 . "LWPOLYLINE") (100 . "AcDbEntity") (8 . "PLANTS") (62 . 94) (370 . 13) (100 . "AcDbPolyline") (90 . 3) (70 . 0)
(43 . 0.0) (10 15516.5893665158 916.2895927602) (10 15497.7375565611 934.0871040724) (10 15482.6527149321
938.9140271493))
((0 . "LWPOLYLINE") (100 . "AcDbEntity") (8 . "PLANTS") (62 . 94) (370 . 13) (100 . "AcDbPolyline") (90 . 3) (70 . 0)
(43 . 0.0) (10 15486.4253393665 3774.5093891403) (10 15497.5842760181 3763.1971719457) (10 15490.1979638009
3695.3238687783))
((0 . "LWPOLYLINE") (100 . "AcDbEntity") (8 . "PLANTS") (62 . 94) (370 . 13) (100 . "AcDbPolyline") (90 . 2) (70 . 0)
(43 . 0.0) (10 15486.4253393665 3774.5093891403) (10 15490.1979638009 3812.2171945701))
((0 . "LWPOLYLINE") (100 . "AcDbEntity") (8 . "PLANTS") (62 . 94) (370 . 13) (100 . "AcDbPolyline") (90 . 2) (70 . 0)
(43 . 0.0) (10 15490.1979638009 3812.2171945701) (10 15509.0497737557 3812.2171945701))
((0 . "LWPOLYLINE") (100 . "AcDbEntity") (8 . "PLANTS") (62 . 94) (370 . 13) (100 . "AcDbPolyline") (90 . 3) (70 . 0)
(43 . 0.0) (10 15546.7590497738 3706.6360859729) (10 15512.82239819 3695.4722850679) (10 15490.1979638009
3695.3238687783))
((0 . "LWPOLYLINE") (100 . "AcDbEntity") (8 . "PLANTS") (62 . 94) (370 . 13) (100 . "AcDbPolyline") (90 . 2) (70 . 0)
(43 . 0.0) (10 15491.9603452708 1255.316442734) (10 15492.0814479638 1191.55260181))
((0 . "LWPOLYLINE") (100 . "AcDbEntity") (8 . "PLANTS") (62 . 94) (370 . 13) (100 . "AcDbPolyline") (90 . 2) (70 . 0)
(43 . 0.0) (10 15492.0814479638 1191.55260181) (10 15520.3619909502 1187.7828054299))
((0 . "LWPOLYLINE") (100 . "AcDbEntity") (8 . "PLANTS") (62 . 94) (370 . 13) (100 . "AcDbPolyline") (90 . 2) (70 . 0)
(43 . 0.0) (10 15512.82239819 4023.3781674208) (10 15493.9649321267 4015.8371040724))
((0 . "LWPOLYLINE") (100 . "AcDbEntity") (8 . "PLANTS") (62 . 94) (370 . 13) (100 . "AcDbPolyline") (90 . 3) (70 . 0)
(43 . 0.0) (10 15531.6742081448 3514.3290723982) (10 15520.5097285068 3509.5014705882) (10 15514.0491680153
3500.4438075486))
((0 . "LWPOLYLINE") (100 . "AcDbEntity") (8 . "PLANTS") (62 . 94) (370 . 13) (100 . "AcDbPolyline") (90 . 2) (70 . 0)
(43 . 0.0) (10 15497.7375565611 3898.9437782805) (10 15497.7375565611 3910.2559954751))
((0 . "LWPOLYLINE") (100 . "AcDbEntity") (8 . "PLANTS") (62 . 94) (370 . 13) (100 . "AcDbPolyline") (90 . 3) (70 . 0)
(43 . 0.0) (10 15497.7375565611 3910.2559954751) (10 15519.1578054299 3929.110520362) (10 15524.1346153846
3951.7349547511))
((0 . "LWPOLYLINE") (100 . "AcDbEntity") (8 . "PLANTS") (62 . 94) (370 . 13) (100 . "AcDbPolyline") (90 . 2) (70 . 0)
(43 . 0.0) (10 15497.7375565611 3898.9437782805) (10 15516.5893665158 3880.0904977376))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15505.2771493213 4208.1447963801 0.0) (10 15530.4737448511 4199.8164249109 0.0) (10 15533.2267372071
4159.7769346201 0.0) (10 15509.0497737557 4147.8125565611 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15505.2771493213 4208.1447963801 0.0) (10 15483.0331793748 4196.9386718691 0.0) (10 15488.6062364188
4156.8555835221 0.0) (10 15509.0497737556 4147.8125565611 0.0))
((0 . "LWPOLYLINE") (100 . "AcDbEntity") (8 . "PLANTS") (62 . 94) (370 . 13) (100 . "AcDbPolyline") (90 . 3) (70 . 0)
(43 . 0.0) (10 15505.2771493213 4208.1447963801) (10 15505.4263574661 4283.4052036199) (10 15509.0497737557
4287.3303167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15505.2771493213 3559.5779411765 0.0) (10 15518.7964338524 3548.119607103 0.0) (10 15532.6329813529
3577.5529789449 0.0) (10 15535.4468325792 3582.2023755656 0.0))
((0 . "LWPOLYLINE") (100 . "AcDbEntity") (8 . "PLANTS") (62 . 94) (370 . 13) (100 . "AcDbPolyline") (90 . 2) (70 . 0)
(43 . 0.0) (10 15505.2771493213 263.9507918552) (10 15505.2771493213 248.8687782805))
((0 . "LWPOLYLINE") (100 . "AcDbEntity") (8 . "PLANTS") (62 . 94) (370 . 13) (100 . "AcDbPolyline") (90 . 2) (70 . 0)
(43 . 0.0) (10 15505.2771493213 263.9507918552) (10 15561.8382352941 309.1996606335))
((0 . "LWPOLYLINE") (100 . "AcDbEntity") (8 . "PLANTS") (62 . 94) (370 . 13) (100 . "AcDbPolyline") (90 . 3) (70 . 0)
(43 . 0.0) (10 15561.8382352941 237.556561086) (10 15531.6742081448 233.9345022624) (10 15505.2771493213
248.8687782805))
((0 . "LWPOLYLINE") (100 . "AcDbEntity") (8 . "PLANTS") (62 . 94) (370 . 13) (100 . "AcDbPolyline") (90 . 2) (70 . 0)
(43 . 0.0) (10 15509.0497737557 4327.731092437) (10 15509.0497737557 4287.3303167421))
((0 . "LWPOLYLINE") (100 . "AcDbEntity") (8 . "PLANTS") (62 . 94) (370 . 13) (100 . "AcDbPolyline") (90 . 3) (70 . 0)
(43 . 0.0) (10 15558.0712669683 4257.1648190045) (10 15539.213800905 4274.9614253394) (10 15509.0497737557
4287.3303167421))
((0 . "LWPOLYLINE") (100 . "AcDbEntity") (8 . "PLANTS") (62 . 94) (370 . 13) (100 . "AcDbPolyline") (90 . 2) (70 . 0)
(43 . 0.0) (10 15509.0497737557 4147.8125565611) (10 15509.0497737557 4132.7304298643))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15561.8382352941 4000.7537330317 0.0) (10 15562.2919033459 4048.6384789073 0.0) (10 15545.6491426053
4100.7214662155 0.0) (10 15509.0497737557 4132.7304298643 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15512.82239819 4023.3781674208 0.0) (10 15515.9032112422 4060.7362826541 0.0) (10 15461.608635514
4107.965899459 0.0) (10 15509.0497737556 4132.7304298643 0.0))
((0 . "LWPOLYLINE") (100 . "AcDbEntity") (8 . "PLANTS") (62 . 94) (370 . 13) (100 . "AcDbPolyline") (90 . 2) (70 . 0)
(43 . 0.0) (10 15509.0497737557 3823.5294117647) (10 15509.0497737557 3812.2171945701))
((0 . "LWPOLYLINE") (100 . "AcDbEntity") (8 . "PLANTS") (62 . 94) (370 . 13) (100 . "AcDbPolyline") (90 . 3) (70 . 0)
(43 . 0.0) (10 15509.0497737557 3823.5294117647) (10 15509.1975113122 3846.1538461538) (10 15516.5893665158
3880.0904977376))
((0 . "LWPOLYLINE") (100 . "AcDbEntity") (8 . "PLANTS") (62 . 94) (370 . 13) (100 . "AcDbPolyline") (90 . 2) (70 . 0)
(43 . 0.0) (10 15509.0497737557 3823.5294117647) (10 15561.8382352941 3834.8416289593))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15546.7590497738 3706.6360859728 0.0) (10 15546.5124012293 3744.4789378725 0.0) (10 15536.5789040563
3784.6207776528 0.0) (10 15509.0497737557 3812.2171945701 0.0))
((0 . "LWPOLYLINE") (100 . "AcDbEntity") (8 . "PLANTS") (62 . 94) (370 . 13) (100 . "AcDbPolyline") (90 . 3) (70 . 0)
(43 . 0.0) (10 15554.2986425339 4000.7537330317) (10 15542.9864253394 4011.010520362) (10 15512.82239819
4023.3781674208))
((0 . "LWPOLYLINE") (100 . "AcDbEntity") (8 . "PLANTS") (62 . 94) (370 . 13) (100 . "AcDbPolyline") (90 . 2) (70 . 0)
(43 . 0.0) (10 15535.4468325792 3887.631561086) (10 15516.5893665158 3880.0904977376))
((0 . "LWPOLYLINE") (100 . "AcDbEntity") (8 . "PLANTS") (62 . 94) (370 . 13) (100 . "AcDbPolyline") (90 . 2) (70 . 0)
(43 . 0.0) (10 15516.5893665158 1036.9541855204) (10 15516.5893665158 1018.0995475113))
((0 . "LWPOLYLINE") (100 . "AcDbEntity") (8 . "PLANTS") (62 . 94) (370 . 13) (100 . "AcDbPolyline") (90 . 3) (70 . 0)
(43 . 0.0) (10 15516.5893665158 1036.9541855204) (10 15526.7057692308 1048.2664027149) (10 15535.4468325792
1070.8908371041))
((0 . "LWPOLYLINE") (100 . "AcDbEntity") (8 . "PLANTS") (62 . 94) (370 . 13) (100 . "AcDbPolyline") (90 . 2) (70 . 0)
(43 . 0.0) (10 15535.4468325792 1006.7873303167) (10 15516.5893665158 1018.0995475113))
((0 . "LWPOLYLINE") (100 . "AcDbEntity") (8 . "PLANTS") (62 . 94) (370 . 13) (100 . "AcDbPolyline") (90 . 2) (70 . 0)
(43 . 0.0) (10 15516.5893665158 916.2895927602) (10 15516.5893665158 908.7471719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15516.5893665158 916.2895927602 0.0) (10 15534.6926351391 932.9622787656 0.0) (10 15510.9414522878
971.1514275991 0.0) (10 15535.4468325792 980.3930995475 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15603.3201357466 912.5197963801 0.0) (10 15579.4391588559 890.2494833412 0.0) (10 15542.619040315
893.1360262202 0.0) (10 15516.5893665158 908.7471719457 0.0))
((0 . "LWPOLYLINE") (100 . "AcDbEntity") (8 . "PLANTS") (62 . 94) (370 . 13) (100 . "AcDbPolyline") (90 . 2) (70 . 0)
(43 . 0.0) (10 15516.5893665158 354.4485294118) (10 15550.5260180995 354.4485294118))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.693100454) (40 .
1) (40 . 1) (40 . 1) (40 . 1) (10 15516.5893665158 354.4485294118 0.0) (10 15510.1315456286 386.1619593515 0.0) (10
15523.7462199556 435.029118293 0.0) (10 15523.1607768409 481.2368686103 0.0) (10 15531.6742081447 493.967760181 0.0))
((0 . "LWPOLYLINE") (100 . "AcDbEntity") (8 . "PLANTS") (62 . 94) (370 . 13) (100 . "AcDbPolyline") (90 . 3) (70 . 0)
(43 . 0.0) (10 15524.1346153846 3951.7349547511) (10 15539.3643665158 3970.4335972851) (10 15550.5260180995
3974.3593891403))
((0 . "LWPOLYLINE") (100 . "AcDbEntity") (8 . "PLANTS") (62 . 94) (370 . 13) (100 . "AcDbPolyline") (90 . 3) (70 . 0)
(43 . 0.0) (10 15526.0180995475 3618.0238687783) (10 15531.4588235294 3608.6649321267) (10 15535.4468325792
3582.2023755656))
((0 . "LWPOLYLINE") (100 . "AcDbEntity") (8 . "PLANTS") (62 . 94) (370 . 13) (100 . "AcDbPolyline") (90 . 2) (70 . 0)
(43 . 0.0) (10 15526.0180995475 3618.0238687783) (10 15558.0712669683 3634.9928733032))
((0 . "LWPOLYLINE") (100 . "AcDbEntity") (8 . "PLANTS") (62 . 94) (370 . 13) (100 . "AcDbPolyline") (90 . 2) (70 . 0)
(43 . 0.0) (10 15530.9075552069 498.5653789991) (10 15531.6742081448 493.967760181))
((0 . "LWPOLYLINE") (100 . "AcDbEntity") (8 . "PLANTS") (62 . 94) (370 . 13) (100 . "AcDbPolyline") (90 . 2) (70 . 0)
(43 . 0.0) (10 15539.213800905 3499.2455882353) (10 15531.6742081448 3514.3290723982))
((0 . "LWPOLYLINE") (100 . "AcDbEntity") (8 . "PLANTS") (62 . 94) (370 . 13) (100 . "AcDbPolyline") (90 . 2) (70 . 0)
(43 . 0.0) (10 15531.6742081448 3514.3290723982) (10 15539.213800905 3533.182239819))
((0 . "LWPOLYLINE") (100 . "AcDbEntity") (8 . "PLANTS") (62 . 94) (370 . 13) (100 . "AcDbPolyline") (90 . 3) (70 . 0)
(43 . 0.0) (10 15531.6742081448 493.967760181) (10 15542.9864253394 490.0418552036) (10 15561.8382352941
471.3433257919))
((0 . "LWPOLYLINE") (100 . "AcDbEntity") (8 . "PLANTS") (62 . 94) (370 . 13) (100 . "AcDbPolyline") (90 . 2) (70 . 0)
(43 . 0.0) (10 15535.4468325792 3887.631561086) (10 15565.6108597285 3876.3193438914))
((0 . "LWPOLYLINE") (100 . "AcDbEntity") (8 . "PLANTS") (62 . 94) (370 . 13) (100 . "AcDbPolyline") (90 . 3) (70 . 0)
(43 . 0.0) (10 15569.3834841629 3944.1926470588) (10 15540.4124434389 3902.7149321267) (10 15535.4468325792
3887.631561086))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5697111423) (40
. 1) (40 . 1) (40 . 1) (40 . 1) (10 15535.4468325791 3582.2023755656 0.0) (10 15565.3966725677 3573.9649261073 0.0) (10
15587.4338153691 3529.4764183518 0.0) (10 15583.7598107799 3479.5789520005 0.0) (10 15599.5475113121 3465.3089366516
0.0))
((0 . "LWPOLYLINE") (100 . "AcDbEntity") (8 . "PLANTS") (62 . 94) (370 . 13) (100 . "AcDbPolyline") (90 . 2) (70 . 0)
(43 . 0.0) (10 15558.0693438914 1155.7324660633) (10 15535.4468325792 1157.6159502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15535.4468325792 1070.8908371041 0.0) (10 15513.1149435487 1093.8794995147 0.0) (10 15517.2174743811
1133.537384373 0.0) (10 15535.4468325792 1157.6159502262 0.0))
((0 . "LWPOLYLINE") (100 . "AcDbEntity") (8 . "PLANTS") (62 . 94) (370 . 13) (100 . "AcDbPolyline") (90 . 3) (70 . 0)
(43 . 0.0) (10 15558.0693438914 1155.7324660633) (10 15558.0693438914 1180.2403846154) (10 15558.0693438914
1241.1685520362))
((0 . "LWPOLYLINE") (100 . "AcDbEntity") (8 . "PLANTS") (62 . 94) (370 . 13) (100 . "AcDbPolyline") (90 . 3) (70 . 0)
(43 . 0.0) (10 15531.6742081448 1255.0607287449) (10 15531.6742081448 1195.3252262443) (10 15535.4468325792
1157.6159502262))
((0 . "LWPOLYLINE") (100 . "AcDbEntity") (8 . "PLANTS") (62 . 94) (370 . 13) (100 . "AcDbPolyline") (90 . 2) (70 . 0)
(43 . 0.0) (10 15535.4468325792 1070.8908371041) (10 15550.5260180995 1070.8908371041))
((0 . "LWPOLYLINE") (100 . "AcDbEntity") (8 . "PLANTS") (62 . 94) (370 . 13) (100 . "AcDbPolyline") (90 . 2) (70 . 0)
(43 . 0.0) (10 15535.4468325792 1006.7873303167) (10 15535.4468325792 980.3930995475))
((0 . "LWPOLYLINE") (100 . "AcDbEntity") (8 . "PLANTS") (62 . 94) (370 . 13) (100 . "AcDbPolyline") (90 . 3) (70 . 0)
(43 . 0.0) (10 15535.4468325792 1006.7873303167) (10 15542.9933257919 1010.4100678733) (10 15569.3834841629
1010.5571266968))
((0 . "LWPOLYLINE") (100 . "AcDbEntity") (8 . "PLANTS") (62 . 94) (370 . 13) (100 . "AcDbPolyline") (90 . 3) (70 . 0)
(43 . 0.0) (10 15565.6108597285 972.850678733) (10 15546.7590497738 973.0053167421) (10 15535.4468325792
980.3930995475))
((0 . "LWPOLYLINE") (100 . "AcDbEntity") (8 . "PLANTS") (62 . 94) (370 . 13) (100 . "AcDbPolyline") (90 . 2) (70 . 0)
(43 . 0.0) (10 15539.213800905 3469.0802036199) (10 15539.3138704424 3431.1463380342))
((0 . "LWPOLYLINE") (100 . "AcDbEntity") (8 . "PLANTS") (62 . 94) (370 . 13) (100 . "AcDbPolyline") (90 . 3) (70 . 0)
(43 . 0.0) (10 15561.8382352941 3668.9295248869) (10 15557.0134615385 3695.3238687783) (10 15546.7590497738
3706.6360859729))
((0 . "LWPOLYLINE") (100 . "AcDbEntity") (8 . "PLANTS") (62 . 94) (370 . 13) (100 . "AcDbPolyline") (90 . 2) (70 . 0)
(43 . 0.0) (10 15558.0712669683 3642.5339366516) (10 15546.7590497738 3653.8461538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15550.5260180995 4204.3736425339 0.0) (10 15574.63924598 4172.8626814155 0.0) (10 15557.1345241173
4121.1283062523 0.0) (10 15588.2352941176 4095.0226244343 0.0))
((0 . "LWPOLYLINE") (100 . "AcDbEntity") (8 . "PLANTS") (62 . 94) (370 . 13) (100 . "AcDbPolyline") (90 . 3) (70 . 0)
(43 . 0.0) (10 15569.3834841629 3944.1926470588) (10 15560.7832579186 3963.0464932127) (10 15550.5260180995
3974.3593891403))
((0 . "LWPOLYLINE") (100 . "AcDbEntity") (8 . "PLANTS") (62 . 94) (370 . 13) (100 . "AcDbPolyline") (90 . 2) (70 . 0)
(43 . 0.0) (10 15554.2986425339 4000.7537330317) (10 15550.5260180995 3974.3593891403))
((0 . "LWPOLYLINE") (100 . "AcDbEntity") (8 . "PLANTS") (62 . 94) (370 . 13) (100 . "AcDbPolyline") (90 . 2) (70 . 0)
(43 . 0.0) (10 15558.0693438914 1155.7324660633) (10 15550.5260180995 1127.4519230769))
((0 . "LWPOLYLINE") (100 . "AcDbEntity") (8 . "PLANTS") (62 . 94) (370 . 13) (100 . "AcDbPolyline") (90 . 3) (70 . 0)
(43 . 0.0) (10 15588.2352941176 1052.036199095) (10 15569.3834841629 1065.9148190045) (10 15550.5260180995
1070.8908371041))
((0 . "LWPOLYLINE") (100 . "AcDbEntity") (8 . "PLANTS") (62 . 94) (370 . 13) (100 . "AcDbPolyline") (90 . 2) (70 . 0)
(43 . 0.0) (10 15550.5260180995 1070.8908371041) (10 15558.0712669683 1089.7426470588))
((0 . "LWPOLYLINE") (100 . "AcDbEntity") (8 . "PLANTS") (62 . 94) (370 . 13) (100 . "AcDbPolyline") (90 . 3) (70 . 0)
(43 . 0.0) (10 15550.5260180995 354.4485294118) (10 15554.4519230769 320.5118778281) (10 15561.8382352941
309.1996606335))
((0 . "LWPOLYLINE") (100 . "AcDbEntity") (8 . "PLANTS") (62 . 94) (370 . 13) (100 . "AcDbPolyline") (90 . 2) (70 . 0)
(43 . 0.0) (10 15554.2986425339 373.3031674208) (10 15550.5260180995 354.4485294118))
((0 . "LWPOLYLINE") (100 . "AcDbEntity") (8 . "PLANTS") (62 . 94) (370 . 13) (100 . "AcDbPolyline") (90 . 2) (70 . 0)
(43 . 0.0) (10 15554.2986425339 4000.7537330317) (10 15561.8382352941 4000.7537330317))
((0 . "LWPOLYLINE") (100 . "AcDbEntity") (8 . "PLANTS") (62 . 94) (370 . 13) (100 . "AcDbPolyline") (90 . 2) (70 . 0)
(43 . 0.0) (10 15584.4626696833 373.3031674208) (10 15554.2986425339 373.3031674208))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5119649046) (40
. 1) (40 . 1) (40 . 1) (40 . 1) (10 15554.2986425339 373.3031674208 0.0) (10 15551.9751695821 392.4492732589 0.0) (10
15566.067782894 425.9641693575 0.0) (10 15579.5750570924 460.2025326261 0.0) (10 15587.8875979623 475.2553615082 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15558.0693438914 1155.7324660633 0.0) (10 15591.8347879925 1153.3724148029 0.0) (10 15593.9741494572
1202.6245196831 0.0) (10 15592.0059954751 1223.3071564658 0.0))
((0 . "LWPOLYLINE") (100 . "AcDbEntity") (8 . "PLANTS") (62 . 94) (370 . 13) (100 . "AcDbPolyline") (90 . 2) (70 . 0)
(43 . 0.0) (10 15618.4012443439 1209.4149202191) (10 15618.4012443439 1168.9281674208))
((0 . "LWPOLYLINE") (100 . "AcDbEntity") (8 . "PLANTS") (62 . 94) (370 . 13) (100 . "AcDbPolyline") (90 . 3) (70 . 0)
(43 . 0.0) (10 15558.0712669683 4257.1648190045) (10 15561.9943438914 4245.8588235294) (10 15576.9230769231
4238.3102941176))
((0 . "LWPOLYLINE") (100 . "AcDbEntity") (8 . "PLANTS") (62 . 94) (370 . 13) (100 . "AcDbPolyline") (90 . 2) (70 . 0)
(43 . 0.0) (10 15573.1504524887 4272.2469457014) (10 15558.0712669683 4257.1648190045))
((0 . "LWPOLYLINE") (100 . "AcDbEntity") (8 . "PLANTS") (62 . 94) (370 . 13) (100 . "AcDbPolyline") (90 . 2) (70 . 0)
(43 . 0.0) (10 15558.0712669683 3642.5339366516) (10 15558.0712669683 3634.9928733032))
((0 . "LWPOLYLINE") (100 . "AcDbEntity") (8 . "PLANTS") (62 . 94) (370 . 13) (100 . "AcDbPolyline") (90 . 2) (70 . 0)
(43 . 0.0) (10 15558.0712669683 3642.5339366516) (10 15561.8382352941 3668.9295248869))
((0 . "LWPOLYLINE") (100 . "AcDbEntity") (8 . "PLANTS") (62 . 94) (370 . 13) (100 . "AcDbPolyline") (90 . 2) (70 . 0)
(43 . 0.0) (10 15588.2352941176 3627.4505656109) (10 15558.0712669683 3634.9928733032))
((0 . "LWPOLYLINE") (100 . "AcDbEntity") (8 . "PLANTS") (62 . 94) (370 . 13) (100 . "AcDbPolyline") (90 . 2) (70 . 0)
(43 . 0.0) (10 15612.7432126697 4000.7537330317) (10 15561.8382352941 4000.7537330317))
((0 . "LWPOLYLINE") (100 . "AcDbEntity") (8 . "PLANTS") (62 . 94) (370 . 13) (100 . "AcDbPolyline") (90 . 3) (70 . 0)
(43 . 0.0) (10 15614.6323529412 3823.5294117647) (10 15576.9230769231 3827.4484162896) (10 15561.8382352941
3834.8416289593))
((0 . "LWPOLYLINE") (100 . "AcDbEntity") (8 . "PLANTS") (62 . 94) (370 . 13) (100 . "AcDbPolyline") (90 . 2) (70 . 0)
(43 . 0.0) (10 15561.8382352941 3834.8416289593) (10 15565.6108597285 3861.2372171946))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.1884139656)
(40 . 0.2988065592) (40 . 0.459148937) (40 . 1) (40 . 1) (40 . 1) (40 . 1) (10 15576.923076923 3774.5093891403 0.0) (10
15588.9778473939 3775.114575471 0.0) (10 15596.5308767879 3764.0552244299 0.0) (10 15602.8718721579 3742.0736455138 0.0)
(10 15630.4220413418 3710.82295894 0.0) (10 15571.4914693211 3678.4959836884 0.0) (10 15561.8382352941 3668.9295248869
0.0))
((0 . "LWPOLYLINE") (100 . "AcDbEntity") (8 . "PLANTS") (62 . 94) (370 . 13) (100 . "AcDbPolyline") (90 . 3) (70 . 0)
(43 . 0.0) (10 15561.8382352941 309.1996606335) (10 15599.5475113122 323.2335972851) (10 15614.6323529412
324.2845022624))
((0 . "LWPOLYLINE") (100 . "AcDbEntity") (8 . "PLANTS") (62 . 94) (370 . 13) (100 . "AcDbPolyline") (90 . 3) (70 . 0)
(43 . 0.0) (10 15561.8382352941 237.556561086) (10 15580.6957013575 233.7867647059) (10 15622.1719457014 237.556561086))
((0 . "LWPOLYLINE") (100 . "AcDbEntity") (8 . "PLANTS") (62 . 94) (370 . 13) (100 . "AcDbPolyline") (90 . 2) (70 . 0)
(43 . 0.0) (10 15561.8382352941 237.556561086) (10 15565.6108597285 256.411199095))
((0 . "LWPOLYLINE") (100 . "AcDbEntity") (8 . "PLANTS") (62 . 94) (370 . 13) (100 . "AcDbPolyline") (90 . 2) (70 . 0)
(43 . 0.0) (10 15565.6108597285 3861.2372171946) (10 15565.6108597285 3876.3193438914))
((0 . "LWPOLYLINE") (100 . "AcDbEntity") (8 . "PLANTS") (62 . 94) (370 . 13) (100 . "AcDbPolyline") (90 . 3) (70 . 0)
(43 . 0.0) (10 15599.5475113122 3917.7983031674) (10 15591.8573529412 3898.9444570136) (10 15565.6108597285
3876.3193438914))
((0 . "LWPOLYLINE") (100 . "AcDbEntity") (8 . "PLANTS") (62 . 94) (370 . 13) (100 . "AcDbPolyline") (90 . 2) (70 . 0)
(43 . 0.0) (10 15610.8597285068 3861.2372171946) (10 15565.6108597285 3861.2372171946))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15565.6108597285 972.850678733 0.0) (10 15555.7342209409 933.1525338149 0.0) (10 15590.0020252726
955.3429327584 0.0) (10 15603.3201357466 938.9140271493 0.0))
((0 . "LWPOLYLINE") (100 . "AcDbEntity") (8 . "PLANTS") (62 . 94) (370 . 13) (100 . "AcDbPolyline") (90 . 2) (70 . 0)
(43 . 0.0) (10 15565.6108597285 972.850678733) (10 15569.3834841629 1010.5571266968))
((0 . "LWPOLYLINE") (100 . "AcDbEntity") (8 . "PLANTS") (62 . 94) (370 . 13) (100 . "AcDbPolyline") (90 . 3) (70 . 0)
(43 . 0.0) (10 15569.3834841629 3944.1926470588) (10 15588.0875565611 3935.5949095023) (10 15599.5475113122
3917.7983031674))
((0 . "LWPOLYLINE") (100 . "AcDbEntity") (8 . "PLANTS") (62 . 94) (370 . 13) (100 . "AcDbPolyline") (90 . 2) (70 . 0)
(43 . 0.0) (10 15569.3834841629 3378.5824660633) (10 15580.6957013575 3378.5824660633))
((0 . "LWPOLYLINE") (100 . "AcDbEntity") (8 . "PLANTS") (62 . 94) (370 . 13) (100 . "AcDbPolyline") (90 . 2) (70 . 0)
(43 . 0.0) (10 15592.007918552 1033.181561086) (10 15569.3834841629 1010.5571266968))
((0 . "LWPOLYLINE") (100 . "AcDbEntity") (8 . "PLANTS") (62 . 94) (370 . 13) (100 . "AcDbPolyline") (90 . 3) (70 . 0)
(43 . 0.0) (10 15573.1504524887 4272.2469457014) (10 15576.7753393665 4264.6996606335) (10 15576.9230769231
4238.3102941176))
((0 . "LWPOLYLINE") (100 . "AcDbEntity") (8 . "PLANTS") (62 . 94) (370 . 13) (100 . "AcDbPolyline") (90 . 2) (70 . 0)
(43 . 0.0) (10 15573.1504524887 4272.2469457014) (10 15572.2629787436 4354.8224660032))
((0 . "LWPOLYLINE") (100 . "AcDbEntity") (8 . "PLANTS") (62 . 94) (370 . 13) (100 . "AcDbPolyline") (90 . 3) (70 . 0)
(43 . 0.0) (10 15610.8597285068 4215.6858597285) (10 15580.8489819005 4228.0547511312) (10 15576.9230769231
4238.3102941176))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15576.9230769231 3344.6458144796 0.0) (10 15591.2486943491 3341.9863085846 0.0) (10 15595.3758077511
3376.1861058812 0.0) (10 15580.6957013575 3378.5824660633 0.0))
((0 . "LWPOLYLINE") (100 . "AcDbEntity") (8 . "PLANTS") (62 . 94) (370 . 13) (100 . "AcDbPolyline") (90 . 2) (70 . 0)
(43 . 0.0) (10 15580.6957013575 3412.5191176471) (10 15580.6957013575 3378.5824660633))
((0 . "LWPOLYLINE") (100 . "AcDbEntity") (8 . "PLANTS") (62 . 94) (370 . 13) (100 . "AcDbPolyline") (90 . 3) (70 . 0)
(43 . 0.0) (10 15599.5475113122 369.5333710407) (10 15588.2352941176 369.5333710407) (10 15584.4626696833
373.3031674208))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15584.4626696833 373.3031674208 0.0) (10 15578.2106150709 394.7290682473 0.0) (10 15609.0338185969
407.4580604217 0.0) (10 15614.6323529412 380.8455882353 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15612.7432126697 4000.7537330317 0.0) (10 15617.5864310019 4035.6875639995 0.0) (10 15584.2565880662
4060.0123354841 0.0) (10 15588.2352941176 4095.0226244344 0.0))
((0 . "LWPOLYLINE") (100 . "AcDbEntity") (8 . "PLANTS") (62 . 94) (370 . 13) (100 . "AcDbPolyline") (90 . 3) (70 . 0)
(43 . 0.0) (10 15603.3201357466 4121.4182126697) (10 15598.3516968326 4106.334841629) (10 15588.2352941176
4095.0226244344))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15588.2352941177 3627.4505656109 0.0) (10 15584.074020302 3607.5044925311 0.0) (10 15614.8460799997
3593.2138475705 0.0) (10 15603.3201357466 3574.6606334842 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15588.2352941176 3627.4505656109 0.0) (10 15596.3242749398 3658.4307260606 0.0) (10 15631.6425067802
3653.8575113839 0.0) (10 15644.7963800905 3634.9928733032 0.0))
((0 . "LWPOLYLINE") (100 . "AcDbEntity") (8 . "PLANTS") (62 . 94) (370 . 13) (100 . "AcDbPolyline") (90 . 2) (70 . 0)
(43 . 0.0) (10 15592.007918552 1044.4937782805) (10 15588.2352941176 1052.036199095))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15610.8597285068 1127.4519230769 0.0) (10 15576.7284093117 1123.2661940413 0.0) (10 15591.2531028902
1067.3470043932 0.0) (10 15588.2352941176 1052.036199095 0.0))
((0 . "LWPOLYLINE") (100 . "AcDbEntity") (8 . "PLANTS") (62 . 94) (370 . 13) (100 . "AcDbPolyline") (90 . 2) (70 . 0)
(43 . 0.0) (10 15592.007918552 1033.181561086) (10 15592.007918552 1044.4937782805))
((0 . "LWPOLYLINE") (100 . "AcDbEntity") (8 . "PLANTS") (62 . 94) (370 . 13) (100 . "AcDbPolyline") (90 . 3) (70 . 0)
(43 . 0.0) (10 15592.007918552 1044.4937782805) (10 15618.246040724 1067.1182126697) (10 15622.1719457014
1078.4304298643))
((0 . "LWPOLYLINE") (100 . "AcDbEntity") (8 . "PLANTS") (62 . 94) (370 . 13) (100 . "AcDbPolyline") (90 . 3) (70 . 0)
(43 . 0.0) (10 15592.007918552 1033.181561086) (10 15622.1719457014 1021.8831447964) (10 15663.6481900453
1033.181561086))
((0 . "LWPOLYLINE") (100 . "AcDbEntity") (8 . "PLANTS") (62 . 94) (370 . 13) (100 . "AcDbPolyline") (90 . 3) (70 . 0)
(43 . 0.0) (10 15641.0237556561 3929.110520362) (10 15625.9445701357 3918.8544117647) (10 15599.5475113122
3917.7983031674))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15599.5475113122 444.9462669683 0.0) (10 15646.2944633566 441.2337262582 0.0) (10 15623.8272088138
397.9309140527 0.0) (10 15650.4524886878 380.8455882353 0.0))
((0 . "LWPOLYLINE") (100 . "AcDbEntity") (8 . "PLANTS") (62 . 94) (370 . 13) (100 . "AcDbPolyline") (90 . 3) (70 . 0)
(43 . 0.0) (10 15599.5475113122 369.5333710407) (10 15604.5228506787 339.3734162896) (10 15614.6323529412
331.8240950226))
((0 . "LWPOLYLINE") (100 . "AcDbEntity") (8 . "PLANTS") (62 . 94) (370 . 13) (100 . "AcDbPolyline") (90 . 2) (70 . 0)
(43 . 0.0) (10 15599.5475113122 369.5333710407) (10 15614.6323529412 380.8455882353))
((0 . "LWPOLYLINE") (100 . "AcDbEntity") (8 . "PLANTS") (62 . 94) (370 . 13) (100 . "AcDbPolyline") (90 . 3) (70 . 0)
(43 . 0.0) (10 15599.5475113122 275.2630090498) (10 15620.967760181 271.3385746606) (10 15622.1719457014 237.556561086))
((0 . "LWPOLYLINE") (100 . "AcDbEntity") (8 . "PLANTS") (62 . 94) (370 . 13) (100 . "AcDbPolyline") (90 . 2) (70 . 0)
(43 . 0.0) (10 15603.3182126697 6876.5710878582) (10 15603.3182126697 6730.7692307692))
((0 . "LWPOLYLINE") (100 . "AcDbEntity") (8 . "PLANTS") (62 . 94) (370 . 13) (100 . "AcDbPolyline") (90 . 2) (70 . 0)
(43 . 0.0) (10 15603.3201357466 938.9140271493) (10 15603.3201357466 912.5197963801))
((0 . "LWPOLYLINE") (100 . "AcDbEntity") (8 . "PLANTS") (62 . 94) (370 . 13) (100 . "AcDbPolyline") (90 . 3) (70 . 0)
(43 . 0.0) (10 15610.8597285068 946.4564479638) (10 15607.0871040724 946.4564479638) (10 15603.3201357466
938.9140271493))
((0 . "LWPOLYLINE") (100 . "AcDbEntity") (8 . "PLANTS") (62 . 94) (370 . 13) (100 . "AcDbPolyline") (90 . 3) (70 . 0)
(43 . 0.0) (10 15652.3359728507 901.2075791855) (10 15622.1719457014 901.3553167421) (10 15603.3201357466
912.5197963801))
((0 . "LWPOLYLINE") (100 . "AcDbEntity") (8 . "PLANTS") (62 . 94) (370 . 13) (100 . "AcDbPolyline") (90 . 3) (70 . 0)
(43 . 0.0) (10 15625.9445701357 4177.9792986425) (10 15615.8281674208 4189.2915158371) (10 15610.8597285068
4215.6858597285))
((0 . "LWPOLYLINE") (100 . "AcDbEntity") (8 . "PLANTS") (62 . 94) (370 . 13) (100 . "AcDbPolyline") (90 . 3) (70 . 0)
(43 . 0.0) (10 15610.8597285068 4215.6858597285) (10 15622.1650452489 4306.1835972851) (10 15622.2070448154
4309.8670033461))
((0 . "LWPOLYLINE") (100 . "AcDbEntity") (8 . "PLANTS") (62 . 94) (370 . 13) (100 . "AcDbPolyline") (90 . 3) (70 . 0)
(43 . 0.0) (10 15614.6323529412 3823.5294117647) (10 15614.4831447964 3853.6886877828) (10 15610.8597285068
3861.2372171946))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15610.8597285068 3861.2372171946 0.0) (10 15615.7840178017 3880.4706666662 0.0) (10 15645.2555543249
3858.8749874913 0.0) (10 15652.3359728507 3880.0904977376 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15610.8597285068 1127.4519230769 0.0) (10 15631.1919166342 1116.3648553524 0.0) (10 15610.9334368329
1093.9480818417 0.0) (10 15622.1719457014 1078.4304298643 0.0))
((0 . "LWPOLYLINE") (100 . "AcDbEntity") (8 . "PLANTS") (62 . 94) (370 . 13) (100 . "AcDbPolyline") (90 . 2) (70 . 0)
(43 . 0.0) (10 15610.8597285068 1127.4519230769) (10 15618.4012443439 1168.9281674208))
((0 . "LWPOLYLINE") (100 . "AcDbEntity") (8 . "PLANTS") (62 . 94) (370 . 13) (100 . "AcDbPolyline") (90 . 3) (70 . 0)
(43 . 0.0) (10 15610.8597285068 946.4564479638) (10 15633.4841628959 946.3080316742) (10 15652.3359728507
938.9140271493))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15610.8597285068 946.4564479638 0.0) (10 15610.0189681797 969.7243923061 0.0) (10 15638.0603035775
1003.9613107396 0.0) (10 15663.6481900453 987.9326923077 0.0))
((0 . "LWPOLYLINE") (100 . "AcDbEntity") (8 . "PLANTS") (62 . 94) (370 . 13) (100 . "AcDbPolyline") (90 . 2) (70 . 0)
(43 . 0.0) (10 15612.7432126697 4000.7537330317) (10 15629.7115384615 3981.9004524887))
((0 . "LWPOLYLINE") (100 . "AcDbEntity") (8 . "PLANTS") (62 . 94) (370 . 13) (100 . "AcDbPolyline") (90 . 2) (70 . 0)
(43 . 0.0) (10 15612.7432126697 4000.7537330317) (10 15641.0237556561 4015.8371040724))
((0 . "LWPOLYLINE") (100 . "AcDbEntity") (8 . "PLANTS") (62 . 94) (370 . 13) (100 . "AcDbPolyline") (90 . 2) (70 . 0)
(43 . 0.0) (10 15614.6323529412 3823.5294117647) (10 15641.0237556561 3819.7582579186))
((0 . "LWPOLYLINE") (100 . "AcDbEntity") (8 . "PLANTS") (62 . 94) (370 . 13) (100 . "AcDbPolyline") (90 . 2) (70 . 0)
(43 . 0.0) (10 15614.6323529412 380.8455882353) (10 15650.4524886878 380.8455882353))
((0 . "LWPOLYLINE") (100 . "AcDbEntity") (8 . "PLANTS") (62 . 94) (370 . 13) (100 . "AcDbPolyline") (90 . 2) (70 . 0)
(43 . 0.0) (10 15614.6323529412 331.8240950226) (10 15614.6323529412 324.2845022624))
((0 . "LWPOLYLINE") (100 . "AcDbEntity") (8 . "PLANTS") (62 . 94) (370 . 13) (100 . "AcDbPolyline") (90 . 2) (70 . 0)
(43 . 0.0) (10 15614.6323529412 331.8240950226) (10 15652.3359728507 358.2211538462))
((0 . "LWPOLYLINE") (100 . "AcDbEntity") (8 . "PLANTS") (62 . 94) (370 . 13) (100 . "AcDbPolyline") (90 . 3) (70 . 0)
(43 . 0.0) (10 15656.1085972851 301.6600678733) (10 15629.8621040724 302.8634615385) (10 15614.6323529412
324.2845022624))
((0 . "LWPOLYLINE") (100 . "AcDbEntity") (8 . "PLANTS") (62 . 94) (370 . 13) (100 . "AcDbPolyline") (90 . 2) (70 . 0)
(43 . 0.0) (10 15663.6481900453 1168.9281674208) (10 15618.4012443439 1168.9281674208))
((0 . "LWPOLYLINE") (100 . "AcDbEntity") (8 . "PLANTS") (62 . 94) (370 . 13) (100 . "AcDbPolyline") (90 . 2) (70 . 0)
(43 . 0.0) (10 15669.3042986425 1082.2030542986) (10 15622.1719457014 1078.4304298643))
((0 . "LWPOLYLINE") (100 . "AcDbEntity") (8 . "PLANTS") (62 . 94) (370 . 13) (100 . "AcDbPolyline") (90 . 3) (70 . 0)
(43 . 0.0) (10 15674.9604072398 245.0989819005) (10 15663.6481900453 237.711199095) (10 15622.1719457014 237.556561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15625.9445701358 4177.9792986425 0.0) (10 15630.6093924099 4169.6323669088 0.0) (10 15616.6157289864
4131.1501560094 0.0) (10 15637.2567873303 4125.1881221719 0.0))
((0 . "LWPOLYLINE") (100 . "AcDbEntity") (8 . "PLANTS") (62 . 94) (370 . 13) (100 . "AcDbPolyline") (90 . 3) (70 . 0)
(43 . 0.0) (10 15625.9445701357 4177.9792986425) (10 15647.3634615385 4196.8325791855) (10 15655.5680143407
4226.4645795328))
((0 . "LWPOLYLINE") (100 . "AcDbEntity") (8 . "PLANTS") (62 . 94) (370 . 13) (100 . "AcDbPolyline") (90 . 3) (70 . 0)
(43 . 0.0) (10 15641.0237556561 3929.110520362) (10 15633.6319004525 3944.1926470588) (10 15629.7115384615
3981.9004524887))
((0 . "LWPOLYLINE") (100 . "AcDbEntity") (8 . "PLANTS") (62 . 94) (370 . 13) (100 . "AcDbPolyline") (90 . 3) (70 . 0)
(43 . 0.0) (10 15629.7115384615 3981.9004524887) (10 15643.5921945701 3996.9838235294) (10 15641.0237556561
4015.8371040724))
((0 . "LWPOLYLINE") (100 . "AcDbEntity") (8 . "PLANTS") (62 . 94) (370 . 13) (100 . "AcDbPolyline") (90 . 3) (70 . 0)
(43 . 0.0) (10 15641.0237556561 4015.8371040724) (10 15644.789479638 4049.7737556561) (10 15637.2567873303
4125.1881221719))
((0 . "LWPOLYLINE") (100 . "AcDbEntity") (8 . "PLANTS") (62 . 94) (370 . 13) (100 . "AcDbPolyline") (90 . 3) (70 . 0)
(43 . 0.0) (10 15644.7963800905 4140.2714932127) (10 15644.7963800905 4132.7304298643) (10 15637.2567873303
4125.1881221719))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15671.193438914 3710.407239819 0.0) (10 15656.3414466723 3722.1024551364 0.0) (10 15635.6485753261
3737.9018685031 0.0) (10 15637.2567873303 3759.4272624434 0.0))
((0 . "LWPOLYLINE") (100 . "AcDbEntity") (8 . "PLANTS") (62 . 94) (370 . 13) (100 . "AcDbPolyline") (90 . 2) (70 . 0)
(43 . 0.0) (10 15656.1085972851 3925.3393665158) (10 15641.0237556561 3929.110520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15720.2092760181 3812.2171945701 0.0) (10 15703.9234935161 3785.7530656192 0.0) (10 15641.9548666658
3783.1953438529 0.0) (10 15641.023755656 3819.7582579185 0.0))
((0 . "LWPOLYLINE") (100 . "AcDbEntity") (8 . "PLANTS") (62 . 94) (370 . 13) (100 . "AcDbPolyline") (90 . 2) (70 . 0)
(43 . 0.0) (10 15656.1085972851 3842.3826923077) (10 15641.0237556561 3819.7582579186))
((0 . "LWPOLYLINE") (100 . "AcDbEntity") (8 . "PLANTS") (62 . 94) (370 . 13) (100 . "AcDbPolyline") (90 . 2) (70 . 0)
(43 . 0.0) (10 15644.7963800905 6836.3496606335) (10 15659.8812217195 6836.3496606335))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15678.7330316742 3627.4505656109 0.0) (10 15672.3824276941 3612.4348623464 0.0) (10 15639.1896297191
3615.5280737089 0.0) (10 15644.7963800905 3634.9928733032 0.0))
((0 . "LWPOLYLINE") (100 . "AcDbEntity") (8 . "PLANTS") (62 . 94) (370 . 13) (100 . "AcDbPolyline") (90 . 2) (70 . 0)
(43 . 0.0) (10 15671.193438914 3642.5339366516) (10 15644.7963800905 3634.9928733032))
((0 . "LWPOLYLINE") (100 . "AcDbEntity") (8 . "PLANTS") (62 . 94) (370 . 13) (100 . "AcDbPolyline") (90 . 2) (70 . 0)
(43 . 0.0) (10 15650.4524886878 380.8455882353) (10 15652.3359728507 358.2211538462))
((0 . "LWPOLYLINE") (100 . "AcDbEntity") (8 . "PLANTS") (62 . 94) (370 . 13) (100 . "AcDbPolyline") (90 . 2) (70 . 0)
(43 . 0.0) (10 15686.2726244344 418.5520361991) (10 15650.4524886878 380.8455882353))
((0 . "LWPOLYLINE") (100 . "AcDbEntity") (8 . "PLANTS") (62 . 94) (370 . 13) (100 . "AcDbPolyline") (90 . 3) (70 . 0)
(43 . 0.0) (10 15656.1085972851 3842.3826923077) (10 15655.9608597285 3872.5425339367) (10 15652.3359728507
3880.0904977376))
((0 . "LWPOLYLINE") (100 . "AcDbEntity") (8 . "PLANTS") (62 . 94) (370 . 13) (100 . "AcDbPolyline") (90 . 3) (70 . 0)
(43 . 0.0) (10 15656.1085972851 3898.9437782805) (10 15652.4851809955 3895.0188914027) (10 15652.3359728507
3880.0904977376))
((0 . "LWPOLYLINE") (100 . "AcDbEntity") (8 . "PLANTS") (62 . 94) (370 . 13) (100 . "AcDbPolyline") (90 . 3) (70 . 0)
(43 . 0.0) (10 15667.4208144796 1127.4519230769) (10 15656.1085972851 1127.4519230769) (10 15652.3359728507
1123.6792986425))
((0 . "LWPOLYLINE") (100 . "AcDbEntity") (8 . "PLANTS") (62 . 94) (370 . 13) (100 . "AcDbPolyline") (90 . 2) (70 . 0)
(43 . 0.0) (10 15652.3359728507 901.2075791855) (10 15652.3359728507 938.9140271493))
((0 . "LWPOLYLINE") (100 . "AcDbEntity") (8 . "PLANTS") (62 . 94) (370 . 13) (100 . "AcDbPolyline") (90 . 2) (70 . 0)
(43 . 0.0) (10 15667.4208144796 969.0808823529) (10 15652.3359728507 938.9140271493))
((0 . "LWPOLYLINE") (100 . "AcDbEntity") (8 . "PLANTS") (62 . 94) (370 . 13) (100 . "AcDbPolyline") (90 . 3) (70 . 0)
(43 . 0.0) (10 15652.3359728507 901.2075791855) (10 15667.4208144796 897.5902714932) (10 15697.584841629
904.9773755656))
((0 . "LWPOLYLINE") (100 . "AcDbEntity") (8 . "PLANTS") (62 . 94) (370 . 13) (100 . "AcDbPolyline") (90 . 2) (70 . 0)
(43 . 0.0) (10 15671.193438914 350.6787330317) (10 15652.3359728507 358.2211538462))
((0 . "LWPOLYLINE") (100 . "AcDbEntity") (8 . "PLANTS") (62 . 94) (370 . 13) (100 . "AcDbPolyline") (90 . 2) (70 . 0)
(43 . 0.0) (10 15656.1085972851 3925.3393665158) (10 15656.1085972851 3898.9437782805))
((0 . "LWPOLYLINE") (100 . "AcDbEntity") (8 . "PLANTS") (62 . 94) (370 . 13) (100 . "AcDbPolyline") (90 . 3) (70 . 0)
(43 . 0.0) (10 15686.2726244344 3944.1926470588) (10 15667.4208144796 3935.5955882353) (10 15656.1085972851
3925.3393665158))
((0 . "LWPOLYLINE") (100 . "AcDbEntity") (8 . "PLANTS") (62 . 94) (370 . 13) (100 . "AcDbPolyline") (90 . 3) (70 . 0)
(43 . 0.0) (10 15705.1300904977 3895.1738687783) (10 15663.656561086 3895.321719457) (10 15656.1085972851
3898.9437782805))
((0 . "LWPOLYLINE") (100 . "AcDbEntity") (8 . "PLANTS") (62 . 94) (370 . 13) (100 . "AcDbPolyline") (90 . 3) (70 . 0)
(43 . 0.0) (10 15656.1085972851 3842.3826923077) (10 15674.9604072398 3834.9897058824) (10 15712.6696832579
3831.0704751131))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15656.1085972851 301.6600678733 0.0) (10 15643.0706188326 275.098751215 0.0) (10 15679.7558372045
269.8098518803 0.0) (10 15674.9604072398 245.0989819005 0.0))
((0 . "LWPOLYLINE") (100 . "AcDbEntity") (8 . "PLANTS") (62 . 94) (370 . 13) (100 . "AcDbPolyline") (90 . 3) (70 . 0)
(43 . 0.0) (10 15656.1085972851 301.6600678733) (10 15663.656561086 308.0024886878) (10 15674.9604072398
309.1996606335))
((0 . "LWPOLYLINE") (100 . "AcDbEntity") (8 . "PLANTS") (62 . 94) (370 . 13) (100 . "AcDbPolyline") (90 . 3) (70 . 0)
(43 . 0.0) (10 15659.8812217195 6836.3496606335) (10 15672.2484162896 6787.4851809955) (10 15712.6696832579
6779.7885746606))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.2004039118) (40
. 1) (40 . 1) (40 . 1) (40 . 1) (10 15659.8812217194 6836.3496606336 0.0) (10 15666.2593456249 6841.6496597992 0.0) (10
15703.4959556795 6861.5616957162 0.0) (10 15757.1478230223 6854.5525229652 0.0) (10 15788.0825791855 6840.1209276018
0.0))
((0 . "LWPOLYLINE") (100 . "AcDbEntity") (8 . "PLANTS") (62 . 94) (370 . 13) (100 . "AcDbPolyline") (90 . 3) (70 . 0)
(43 . 0.0) (10 15663.6481900453 1168.9281674208) (10 15667.2730769231 1161.3809954751) (10 15667.4208144796
1138.7641402715))
((0 . "LWPOLYLINE") (100 . "AcDbEntity") (8 . "PLANTS") (62 . 94) (370 . 13) (100 . "AcDbPolyline") (90 . 3) (70 . 0)
(43 . 0.0) (10 15674.9604072398 1006.7873303167) (10 15669.9947963801 1025.6343891403) (10 15663.6481900453
1033.181561086))
((0 . "LWPOLYLINE") (100 . "AcDbEntity") (8 . "PLANTS") (62 . 94) (370 . 13) (100 . "AcDbPolyline") (90 . 2) (70 . 0)
(43 . 0.0) (10 15671.193438914 1052.036199095) (10 15663.6481900453 1033.181561086))
((0 . "LWPOLYLINE") (100 . "AcDbEntity") (8 . "PLANTS") (62 . 94) (370 . 13) (100 . "AcDbPolyline") (90 . 2) (70 . 0)
(43 . 0.0) (10 15667.4208144796 969.0808823529) (10 15663.6481900453 987.9326923077))
((0 . "LWPOLYLINE") (100 . "AcDbEntity") (8 . "PLANTS") (62 . 94) (370 . 13) (100 . "AcDbPolyline") (90 . 2) (70 . 0)
(43 . 0.0) (10 15663.6481900453 987.9326923077) (10 15674.9604072398 1006.7873303167))
((0 . "LWPOLYLINE") (100 . "AcDbEntity") (8 . "PLANTS") (62 . 94) (370 . 13) (100 . "AcDbPolyline") (90 . 2) (70 . 0)
(43 . 0.0) (10 15667.4208144796 1127.4519230769) (10 15667.4208144796 1138.7641402715))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15710.6973934651 1160.837999629 0.0) (10 15690.3715627388 1166.2228064948 0.0) (10 15690.8753558118
1130.4297698146 0.0) (10 15667.4208144796 1138.7641402715 0.0))
((0 . "LWPOLYLINE") (100 . "AcDbEntity") (8 . "PLANTS") (62 . 94) (370 . 13) (100 . "AcDbPolyline") (90 . 2) (70 . 0)
(43 . 0.0) (10 15667.4208144796 1127.4519230769) (10 15669.3042986425 1082.2030542986))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15667.4208144796 969.0808823529 0.0) (10 15701.5390108446 974.9608801154 0.0) (10 15698.7043239706
919.2550357228 0.0) (10 15697.584841629 904.9773755656 0.0))
((0 . "LWPOLYLINE") (100 . "AcDbEntity") (8 . "PLANTS") (62 . 94) (370 . 13) (100 . "AcDbPolyline") (90 . 2) (70 . 0)
(43 . 0.0) (10 15671.193438914 1052.036199095) (10 15669.3042986425 1082.2030542986))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15741.2970335908 1134.0574302595 0.0) (10 15710.2798401617 1125.8410959555 0.0) (10 15704.8848115906
1074.868430679 0.0) (10 15669.3042986425 1082.2030542986 0.0))
((0 . "LWPOLYLINE") (100 . "AcDbEntity") (8 . "PLANTS") (62 . 94) (370 . 13) (100 . "AcDbPolyline") (90 . 2) (70 . 0)
(43 . 0.0) (10 15671.193438914 3710.407239819) (10 15671.193438914 3702.8661764706))
((0 . "LWPOLYLINE") (100 . "AcDbEntity") (8 . "PLANTS") (62 . 94) (370 . 13) (100 . "AcDbPolyline") (90 . 2) (70 . 0)
(43 . 0.0) (10 15671.193438914 3710.407239819) (10 15690.0452488688 3721.7194570136))
((0 . "LWPOLYLINE") (100 . "AcDbEntity") (8 . "PLANTS") (62 . 94) (370 . 13) (100 . "AcDbPolyline") (90 . 2) (70 . 0)
(43 . 0.0) (10 15678.7330316742 3627.4505656109) (10 15671.193438914 3642.5339366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15705.1300904977 3661.3872171946 0.0) (10 15695.6788324503 3677.9260230187 0.0) (10 15664.7663820956
3663.6881593953 0.0) (10 15671.193438914 3642.5339366516 0.0))
((0 . "LWPOLYLINE") (100 . "AcDbEntity") (8 . "PLANTS") (62 . 94) (370 . 13) (100 . "AcDbPolyline") (90 . 3) (70 . 0)
(43 . 0.0) (10 15671.193438914 1052.036199095) (10 15708.8970588235 1060.7757918552) (10 15760.8583369872
1111.7016549493))
((0 . "LWPOLYLINE") (100 . "AcDbEntity") (8 . "PLANTS") (62 . 94) (370 . 13) (100 . "AcDbPolyline") (90 . 2) (70 . 0)
(43 . 0.0) (10 15708.8970588235 350.6787330317) (10 15671.193438914 350.6787330317))
((0 . "LWPOLYLINE") (100 . "AcDbEntity") (8 . "PLANTS") (62 . 94) (370 . 13) (100 . "AcDbPolyline") (90 . 2) (70 . 0)
(43 . 0.0) (10 15671.193438914 350.6787330317) (10 15674.9604072398 309.1996606335))
((0 . "LWPOLYLINE") (100 . "AcDbEntity") (8 . "PLANTS") (62 . 94) (370 . 13) (100 . "AcDbPolyline") (90 . 2) (70 . 0)
(43 . 0.0) (10 15727.7545248869 991.7053167421) (10 15674.9604072398 1006.7873303167))
((0 . "LWPOLYLINE") (100 . "AcDbEntity") (8 . "PLANTS") (62 . 94) (370 . 13) (100 . "AcDbPolyline") (90 . 3) (70 . 0)
(43 . 0.0) (10 15705.1300904977 290.3478506787) (10 15690.0452488688 295.1739819005) (10 15674.9604072398
309.1996606335))
((0 . "LWPOLYLINE") (100 . "AcDbEntity") (8 . "PLANTS") (62 . 94) (370 . 13) (100 . "AcDbPolyline") (90 . 2) (70 . 0)
(43 . 0.0) (10 15705.1300904977 245.0989819005) (10 15674.9604072398 245.0989819005))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6567083906) (40
. 1) (40 . 1) (40 . 1) (40 . 1) (10 15678.7330316741 3627.4505656107 0.0) (10 15707.8010181028 3646.57209752 0.0) (10
15747.5431147613 3585.0987574136 0.0) (10 15692.5768430372 3572.8651070571 0.0) (10 15686.2726244343 3589.7433257919
0.0))
((0 . "LWPOLYLINE") (100 . "AcDbEntity") (8 . "PLANTS") (62 . 94) (370 . 13) (100 . "AcDbPolyline") (90 . 2) (70 . 0)
(43 . 0.0) (10 15686.2726244344 3944.1926470588) (10 15720.2092760181 3944.1926470588))
((0 . "LWPOLYLINE") (100 . "AcDbEntity") (8 . "PLANTS") (62 . 94) (370 . 13) (100 . "AcDbPolyline") (90 . 3) (70 . 0)
(43 . 0.0) (10 15686.2726244344 3944.1926470588) (10 15686.4218325792 3974.3593891403) (10 15693.8178733032
4008.296040724))
((0 . "LWPOLYLINE") (100 . "AcDbEntity") (8 . "PLANTS") (62 . 94) (370 . 13) (100 . "AcDbPolyline") (90 . 3) (70 . 0)
(43 . 0.0) (10 15686.2726244344 467.5707013575) (10 15682.5056561086 452.4886877828) (10 15686.2726244344
418.5520361991))
((0 . "LWPOLYLINE") (100 . "AcDbEntity") (8 . "PLANTS") (62 . 94) (370 . 13) (100 . "AcDbPolyline") (90 . 2) (70 . 0)
(43 . 0.0) (10 15686.2726244344 418.5520361991) (10 15720.2092760181 426.0944570136))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15690.0452488687 4113.8759049773 0.0) (10 15715.4901969162 4084.078837494 0.0) (10 15664.1169930147
4031.2396518093 0.0) (10 15693.8178733031 4008.2960407239 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15690.0452488688 4113.8759049774 0.0) (10 15676.0951946912 4116.8835680561 0.0) (10 15682.2973673843
4137.701212042 0.0) (10 15688.3041025298 4144.6243590601 0.0))
((0 . "LWPOLYLINE") (100 . "AcDbEntity") (8 . "PLANTS") (62 . 94) (370 . 13) (100 . "AcDbPolyline") (90 . 3) (70 . 0)
(43 . 0.0) (10 15690.0452488688 4113.8759049774) (10 15701.2041855204 4128.9592760181) (10 15698.3337510638
4146.9022949686))
((0 . "LWPOLYLINE") (100 . "AcDbEntity") (8 . "PLANTS") (62 . 94) (370 . 13) (100 . "AcDbPolyline") (90 . 3) (70 . 0)
(43 . 0.0) (10 15690.0452488688 3721.7194570136) (10 15691.2410633484 3736.7959276018) (10 15697.584841629
3744.3438914027))
((0 . "LWPOLYLINE") (100 . "AcDbEntity") (8 . "PLANTS") (62 . 94) (370 . 13) (100 . "AcDbPolyline") (90 . 3) (70 . 0)
(43 . 0.0) (10 15690.0452488688 3721.7194570136) (10 15708.8970588235 3721.8740950226) (10 15720.2092760181
3729.260520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15735.2941176471 4057.3148190045 0.0) (10 15710.975413107 4048.2787090962 0.0) (10 15718.836007031
4015.4982727647 0.0) (10 15693.8178733032 4008.296040724 0.0))
((0 . "LWPOLYLINE") (100 . "AcDbEntity") (8 . "PLANTS") (62 . 94) (370 . 13) (100 . "AcDbPolyline") (90 . 2) (70 . 0)
(43 . 0.0) (10 15735.2941176471 904.9773755656) (10 15697.584841629 904.9773755656))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15731.5214932127 460.0311085973 0.0) (10 15730.414749983 483.8648194405 0.0) (10 15689.434957678
485.844359348 0.0) (10 15691.2494343891 508.0776470588 0.0))
((0 . "LWPOLYLINE") (100 . "AcDbEntity") (8 . "PLANTS") (62 . 94) (370 . 13) (100 . "AcDbPolyline") (90 . 2) (70 . 0)
(43 . 0.0) (10 15705.1300904977 3895.1738687783) (10 15716.4423076923 3872.5494343891))
((0 . "LWPOLYLINE") (100 . "AcDbEntity") (8 . "PLANTS") (62 . 94) (370 . 13) (100 . "AcDbPolyline") (90 . 3) (70 . 0)
(43 . 0.0) (10 15750.378959276 3906.4860859729) (10 15720.2092760181 3906.3311085973) (10 15705.1300904977
3895.1738687783))
((0 . "LWPOLYLINE") (100 . "AcDbEntity") (8 . "PLANTS") (62 . 94) (370 . 13) (100 . "AcDbPolyline") (90 . 3) (70 . 0)
(43 . 0.0) (10 15708.8970588235 286.5752262443) (10 15708.8970588235 290.3478506787) (10 15705.1300904977
290.3478506787))
((0 . "LWPOLYLINE") (100 . "AcDbEntity") (8 . "PLANTS") (62 . 94) (370 . 13) (100 . "AcDbPolyline") (90 . 2) (70 . 0)
(43 . 0.0) (10 15708.8970588235 286.5752262443) (10 15705.1300904977 290.3478506787))
((0 . "LWPOLYLINE") (100 . "AcDbEntity") (8 . "PLANTS") (62 . 94) (370 . 13) (100 . "AcDbPolyline") (90 . 2) (70 . 0)
(43 . 0.0) (10 15708.8970588235 350.6787330317) (10 15705.1300904977 290.3478506787))
((0 . "LWPOLYLINE") (100 . "AcDbEntity") (8 . "PLANTS") (62 . 94) (370 . 13) (100 . "AcDbPolyline") (90 . 2) (70 . 0)
(43 . 0.0) (10 15742.8337104072 245.0989819005) (10 15705.1300904977 245.0989819005))
((0 . "LWPOLYLINE") (100 . "AcDbEntity") (8 . "PLANTS") (62 . 94) (370 . 13) (100 . "AcDbPolyline") (90 . 2) (70 . 0)
(43 . 0.0) (10 15708.8970588235 286.5752262443) (10 15705.1300904977 245.0989819005))
((0 . "LWPOLYLINE") (100 . "AcDbEntity") (8 . "PLANTS") (62 . 94) (370 . 13) (100 . "AcDbPolyline") (90 . 3) (70 . 0)
(43 . 0.0) (10 15735.2941176471 6885.3697963801) (10 15723.9819004525 6884.1654977376) (10 15708.8970588235
6874.0575791855))
((0 . "LWPOLYLINE") (100 . "AcDbEntity") (8 . "PLANTS") (62 . 94) (370 . 13) (100 . "AcDbPolyline") (90 . 2) (70 . 0)
(43 . 0.0) (10 15744.7228506787 361.9909502262) (10 15708.8970588235 350.6787330317))
((0 . "LWPOLYLINE") (100 . "AcDbEntity") (8 . "PLANTS") (62 . 94) (370 . 13) (100 . "AcDbPolyline") (90 . 2) (70 . 0)
(43 . 0.0) (10 15708.8970588235 286.5752262443) (10 15731.5214932127 286.5752262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15747.6531207308 6730.7692307692 0.0) (10 15725.9406075961 6734.6801817815 0.0) (10 15705.3891214349
6754.9337052635 0.0) (10 15712.6696832579 6779.7885746606 0.0))
((0 . "LWPOLYLINE") (100 . "AcDbEntity") (8 . "PLANTS") (62 . 94) (370 . 13) (100 . "AcDbPolyline") (90 . 3) (70 . 0)
(43 . 0.0) (10 15776.770361991 6783.559841629) (10 15723.9819004525 6783.4115384615) (10 15712.6696832579
6779.7885746606))
((0 . "LWPOLYLINE") (100 . "AcDbEntity") (8 . "PLANTS") (62 . 94) (370 . 13) (100 . "AcDbPolyline") (90 . 2) (70 . 0)
(43 . 0.0) (10 15720.2092760181 3812.2171945701) (10 15712.6696832579 3831.0704751131))
((0 . "LWPOLYLINE") (100 . "AcDbEntity") (8 . "PLANTS") (62 . 94) (370 . 13) (100 . "AcDbPolyline") (90 . 2) (70 . 0)
(43 . 0.0) (10 15716.4423076923 3872.5494343891) (10 15712.6696832579 3831.0704751131))
((0 . "LWPOLYLINE") (100 . "AcDbEntity") (8 . "PLANTS") (62 . 94) (370 . 13) (100 . "AcDbPolyline") (90 . 2) (70 . 0)
(43 . 0.0) (10 15716.4423076923 3872.5494343891) (10 15750.378959276 3872.5494343891))
((0 . "LWPOLYLINE") (100 . "AcDbEntity") (8 . "PLANTS") (62 . 94) (370 . 13) (100 . "AcDbPolyline") (90 . 2) (70 . 0)
(43 . 0.0) (10 15716.4423076923 3736.8028280543) (10 15720.2092760181 3729.260520362))
((0 . "LWPOLYLINE") (100 . "AcDbEntity") (8 . "PLANTS") (62 . 94) (370 . 13) (100 . "AcDbPolyline") (90 . 3) (70 . 0)
(43 . 0.0) (10 15727.7545248869 976.6204751131) (10 15723.9819004525 976.6204751131) (10 15716.4423076923
965.3082579186))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15720.2092760181 3944.1926470588 0.0) (10 15720.8269785145 3968.0033653581 0.0) (10 15731.089247298
3993.6091840215 0.0) (10 15754.1459276018 4004.5248868778 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15720.2092760181 3944.1926470588 0.0) (10 15745.0820818034 3938.935126128 0.0) (10 15745.7611597642
3971.4872350504 0.0) (10 15769.2307692308 3970.5882352941 0.0))
((0 . "LWPOLYLINE") (100 . "AcDbEntity") (8 . "PLANTS") (62 . 94) (370 . 13) (100 . "AcDbPolyline") (90 . 2) (70 . 0)
(43 . 0.0) (10 15720.2092760181 3812.2171945701) (10 15739.0667420814 3812.2171945701))
((0 . "LWPOLYLINE") (100 . "AcDbEntity") (8 . "PLANTS") (62 . 94) (370 . 13) (100 . "AcDbPolyline") (90 . 3) (70 . 0)
(43 . 0.0) (10 15780.6120870367 3730.5103612982) (10 15765.4581447964 3733.0316742081) (10 15720.2092760181
3729.260520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15744.7228506787 361.9909502262 0.0) (10 15752.7355202029 385.9688147665 0.0) (10 15739.4359215674
411.7972712516 0.0) (10 15720.2092760181 426.0944570136 0.0))
((0 . "LWPOLYLINE") (100 . "AcDbEntity") (8 . "PLANTS") (62 . 94) (370 . 13) (100 . "AcDbPolyline") (90 . 2) (70 . 0)
(43 . 0.0) (10 15731.5214932127 460.0311085973) (10 15720.2092760181 426.0944570136))
((0 . "LWPOLYLINE") (100 . "AcDbEntity") (8 . "PLANTS") (62 . 94) (370 . 13) (100 . "AcDbPolyline") (90 . 2) (70 . 0)
(43 . 0.0) (10 15727.7545248869 976.6204751131) (10 15727.7545248869 991.7053167421))
((0 . "LWPOLYLINE") (100 . "AcDbEntity") (8 . "PLANTS") (62 . 94) (370 . 13) (100 . "AcDbPolyline") (90 . 2) (70 . 0)
(43 . 0.0) (10 15727.7545248869 991.7053167421) (10 15750.378959276 1010.5571266968))
((0 . "LWPOLYLINE") (100 . "AcDbEntity") (8 . "PLANTS") (62 . 94) (370 . 13) (100 . "AcDbPolyline") (90 . 2) (70 . 0)
(43 . 0.0) (10 15727.7545248869 976.6204751131) (10 15795.6278280543 953.996040724))
((0 . "LWPOLYLINE") (100 . "AcDbEntity") (8 . "PLANTS") (62 . 94) (370 . 13) (100 . "AcDbPolyline") (90 . 2) (70 . 0)
(43 . 0.0) (10 15735.2941176471 904.9773755656) (10 15727.7545248869 938.9140271493))
((0 . "LWPOLYLINE") (100 . "AcDbEntity") (8 . "PLANTS") (62 . 94) (370 . 13) (100 . "AcDbPolyline") (90 . 2) (70 . 0)
(43 . 0.0) (10 15731.5214932127 460.0311085973) (10 15750.378959276 463.8009049774))
((0 . "LWPOLYLINE") (100 . "AcDbEntity") (8 . "PLANTS") (62 . 94) (370 . 13) (100 . "AcDbPolyline") (90 . 3) (70 . 0)
(43 . 0.0) (10 15742.8337104072 260.1809954751) (10 15736.4899321267 267.728280543) (10 15731.5214932127
286.5752262443))
((0 . "LWPOLYLINE") (100 . "AcDbEntity") (8 . "PLANTS") (62 . 94) (370 . 13) (100 . "AcDbPolyline") (90 . 2) (70 . 0)
(43 . 0.0) (10 15750.378959276 305.4298642534) (10 15731.5214932127 286.5752262443))
((0 . "LWPOLYLINE") (100 . "AcDbEntity") (8 . "PLANTS") (62 . 94) (370 . 13) (100 . "AcDbPolyline") (90 . 2) (70 . 0)
(43 . 0.0) (10 15735.2941176471 4057.3148190045) (10 15757.9185520362 4038.4615384615))
((0 . "LWPOLYLINE") (100 . "AcDbEntity") (8 . "PLANTS") (62 . 94) (370 . 13) (100 . "AcDbPolyline") (90 . 2) (70 . 0)
(43 . 0.0) (10 15735.2941176471 4057.3148190045) (10 15765.4581447964 4144.0426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15735.2941176471 904.9773755656 0.0) (10 15760.5924169324 891.7759938761 0.0) (10 15814.0255940703
921.5231239171 0.0) (10 15814.0243055844 882.3529411764 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15803.1674208145 3800.9049773756 0.0) (10 15784.3793582613 3788.3288841407 0.0) (10 15749.9469556094
3789.4658981952 0.0) (10 15739.0667420814 3812.2171945701 0.0))
((0 . "LWPOLYLINE") (100 . "AcDbEntity") (8 . "PLANTS") (62 . 94) (370 . 13) (100 . "AcDbPolyline") (90 . 2) (70 . 0)
(43 . 0.0) (10 15757.9185520362 3831.0704751131) (10 15739.0667420814 3812.2171945701))
((0 . "LWPOLYLINE") (100 . "AcDbEntity") (8 . "PLANTS") (62 . 94) (370 . 13) (100 . "AcDbPolyline") (90 . 3) (70 . 0)
(43 . 0.0) (10 15750.378959276 1010.5571266968) (10 15749.1734162896 1021.8693438914) (10 15739.0667420814
1033.181561086))
((0 . "LWPOLYLINE") (100 . "AcDbEntity") (8 . "PLANTS") (62 . 94) (370 . 13) (100 . "AcDbPolyline") (90 . 2) (70 . 0)
(43 . 0.0) (10 15742.8337104072 245.0989819005) (10 15742.8337104072 260.1809954751))
((0 . "LWPOLYLINE") (100 . "AcDbEntity") (8 . "PLANTS") (62 . 94) (370 . 13) (100 . "AcDbPolyline") (90 . 3) (70 . 0)
(43 . 0.0) (10 15787.3300904977 289.5925339367) (10 15765.4581447964 268.9205882353) (10 15742.8337104072
260.1809954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15742.8337104072 245.0989819005 0.0) (10 15755.4454225435 226.8510227989 0.0) (10 15784.1082640649
225.0229803503 0.0) (10 15799.3947963801 241.3263574661 0.0))
((0 . "LWPOLYLINE") (100 . "AcDbEntity") (8 . "PLANTS") (62 . 94) (370 . 13) (100 . "AcDbPolyline") (90 . 2) (70 . 0)
(43 . 0.0) (10 15744.7228506787 361.9909502262) (10 15791.8552036199 361.9909502262))
((0 . "LWPOLYLINE") (100 . "AcDbEntity") (8 . "PLANTS") (62 . 94) (370 . 13) (100 . "AcDbPolyline") (90 . 3) (70 . 0)
(43 . 0.0) (10 15744.7228506787 361.9909502262) (10 15742.982918552 343.1363122172) (10 15750.378959276 305.4298642534))
((0 . "LWPOLYLINE") (100 . "AcDbEntity") (8 . "PLANTS") (62 . 94) (370 . 13) (100 . "AcDbPolyline") (90 . 2) (70 . 0)
(43 . 0.0) (10 15750.378959276 3906.4860859729) (10 15750.378959276 3872.5494343891))
((0 . "LWPOLYLINE") (100 . "AcDbEntity") (8 . "PLANTS") (62 . 94) (370 . 13) (100 . "AcDbPolyline") (90 . 2) (70 . 0)
(43 . 0.0) (10 15750.378959276 3906.4860859729) (10 15769.2307692308 3910.2559954751))
((0 . "LWPOLYLINE") (100 . "AcDbEntity") (8 . "PLANTS") (62 . 94) (370 . 13) (100 . "AcDbPolyline") (90 . 3) (70 . 0)
(43 . 0.0) (10 15780.5429864253 3865.0071266968) (10 15761.6911764706 3865.1621040724) (10 15750.378959276
3872.5494343891))
((0 . "LWPOLYLINE") (100 . "AcDbEntity") (8 . "PLANTS") (62 . 94) (370 . 13) (100 . "AcDbPolyline") (90 . 3) (70 . 0)
(43 . 0.0) (10 15750.378959276 1010.5571266968) (10 15760.4856334842 999.2524886878) (10 15761.6911764706
991.7053167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15791.8552036199 361.9909502262 0.0) (10 15791.7424073672 399.292625373 0.0) (10 15781.5218297052
439.3455360839 0.0) (10 15750.378959276 463.8009049774 0.0))
((0 . "LWPOLYLINE") (100 . "AcDbEntity") (8 . "PLANTS") (62 . 94) (370 . 13) (100 . "AcDbPolyline") (90 . 2) (70 . 0)
(43 . 0.0) (10 15773.0033936652 497.7375565611) (10 15750.378959276 463.8009049774))
((0 . "LWPOLYLINE") (100 . "AcDbEntity") (8 . "PLANTS") (62 . 94) (370 . 13) (100 . "AcDbPolyline") (90 . 3) (70 . 0)
(43 . 0.0) (10 15787.3300904977 289.5925339367) (10 15769.2307692308 304.225) (10 15750.378959276 305.4298642534))
((0 . "LWPOLYLINE") (100 . "AcDbEntity") (8 . "PLANTS") (62 . 94) (370 . 13) (100 . "AcDbPolyline") (90 . 2) (70 . 0)
(43 . 0.0) (10 15754.1459276018 4004.5248868778) (10 15769.2307692308 3989.4415158371))
((0 . "LWPOLYLINE") (100 . "AcDbEntity") (8 . "PLANTS") (62 . 94) (370 . 13) (100 . "AcDbPolyline") (90 . 3) (70 . 0)
(43 . 0.0) (10 15754.1459276018 4004.5248868778) (10 15757.7708144796 4012.0728506787) (10 15757.9185520362
4038.4615384615))
((0 . "LWPOLYLINE") (100 . "AcDbEntity") (8 . "PLANTS") (62 . 94) (370 . 13) (100 . "AcDbPolyline") (90 . 2) (70 . 0)
(43 . 0.0) (10 15765.4581447964 4038.4615384615) (10 15757.9185520362 4038.4615384615))
((0 . "LWPOLYLINE") (100 . "AcDbEntity") (8 . "PLANTS") (62 . 94) (370 . 13) (100 . "AcDbPolyline") (90 . 2) (70 . 0)
(43 . 0.0) (10 15766.8316397448 4201.7006059135) (10 15765.4581447964 4144.0426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15833.3314479638 4177.9792986425 0.0) (10 15821.3028533005 4152.2860135125 0.0) (10 15792.1043661141
4139.4346255859 0.0) (10 15765.4581447964 4144.0426470588 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15765.4581447964 4038.4615384615 0.0) (10 15764.0155402555 4058.0063248694 0.0) (10 15781.0683991229
4073.8357792223 0.0) (10 15795.6278280543 4083.7104072398 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15765.4581447964 4038.4615384615 0.0) (10 15792.5109525397 4026.9934862091 0.0) (10 15822.0334934604
4064.8081504862 0.0) (10 15795.6278280542 4083.7104072398 0.0))
((0 . "LWPOLYLINE") (100 . "AcDbEntity") (8 . "PLANTS") (62 . 94) (370 . 13) (100 . "AcDbPolyline") (90 . 2) (70 . 0)
(43 . 0.0) (10 15769.2307692308 3970.5882352941) (10 15769.2307692308 3989.4415158371))
((0 . "LWPOLYLINE") (100 . "AcDbEntity") (8 . "PLANTS") (62 . 94) (370 . 13) (100 . "AcDbPolyline") (90 . 3) (70 . 0)
(43 . 0.0) (10 15833.3314479638 4012.0659502262) (10 15799.3947963801 4011.009841629) (10 15769.2307692308
3989.4415158371))
((0 . "LWPOLYLINE") (100 . "AcDbEntity") (8 . "PLANTS") (62 . 94) (370 . 13) (100 . "AcDbPolyline") (90 . 2) (70 . 0)
(43 . 0.0) (10 15769.2307692308 3970.5882352941) (10 15788.0825791855 3970.5882352941))
((0 . "LWPOLYLINE") (100 . "AcDbEntity") (8 . "PLANTS") (62 . 94) (370 . 13) (100 . "AcDbPolyline") (90 . 2) (70 . 0)
(43 . 0.0) (10 15784.3156108597 3898.9437782805) (10 15769.2307692308 3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15882.3529411765 3955.5048642534 0.0) (10 15857.3346893796 3904.3178480821 0.0) (10 15783.1192436594
3966.049449897 0.0) (10 15769.2307692308 3910.2559954751 0.0))
((0 . "LWPOLYLINE") (100 . "AcDbEntity") (8 . "PLANTS") (62 . 94) (370 . 13) (100 . "AcDbPolyline") (90 . 3) (70 . 0)
(43 . 0.0) (10 15855.9558823529 6779.7885746606) (10 15844.6436651584 6783.4115384615) (10 15776.770361991
6783.559841629))
((0 . "LWPOLYLINE") (100 . "AcDbEntity") (8 . "PLANTS") (62 . 94) (370 . 13) (100 . "AcDbPolyline") (90 . 3) (70 . 0)
(43 . 0.0) (10 15776.770361991 6783.559841629) (10 15776.9195701357 6809.9547511312) (10 15788.0825791855
6840.1209276018))
((0 . "LWPOLYLINE") (100 . "AcDbEntity") (8 . "PLANTS") (62 . 94) (370 . 13) (100 . "AcDbPolyline") (90 . 3) (70 . 0)
(43 . 0.0) (10 15780.5429864253 3865.0071266968) (10 15791.8483031674 3857.459841629) (10 15803.1674208145
3842.3826923077))
((0 . "LWPOLYLINE") (100 . "AcDbEntity") (8 . "PLANTS") (62 . 94) (370 . 13) (100 . "AcDbPolyline") (90 . 2) (70 . 0)
(43 . 0.0) (10 15784.3156108597 3898.9437782805) (10 15780.5429864253 3865.0071266968))
((0 . "LWPOLYLINE") (100 . "AcDbEntity") (8 . "PLANTS") (62 . 94) (370 . 13) (100 . "AcDbPolyline") (90 . 2) (70 . 0)
(43 . 0.0) (10 15784.3156108597 6907.9942307692) (10 15810.7070135747 6911.7647058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15784.3156108597 6742.0814479638 0.0) (10 15804.4656892784 6729.3463258287 0.0) (10 15831.8406103561
6740.0542568344 0.0) (10 15852.1889140272 6745.8519230769 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15784.3156108597 3898.9437782805 0.0) (10 15827.8905689734 3888.1237933977 0.0) (10 15865.4451538499
3919.2239462288 0.0) (10 15908.75 3914.0271493213 0.0))
((0 . "LWPOLYLINE") (100 . "AcDbEntity") (8 . "PLANTS") (62 . 94) (370 . 13) (100 . "AcDbPolyline") (90 . 3) (70 . 0)
(43 . 0.0) (10 15787.3300904977 289.5925339367) (10 15799.2415158371 271.4932126697) (10 15799.3947963801
241.3263574661))
((0 . "LWPOLYLINE") (100 . "AcDbEntity") (8 . "PLANTS") (62 . 94) (370 . 13) (100 . "AcDbPolyline") (90 . 3) (70 . 0)
(43 . 0.0) (10 15787.3300904977 289.5925339367) (10 15799.2484162896 312.9722850679) (10 15799.3947963801
361.9909502262))
((0 . "LWPOLYLINE") (100 . "AcDbEntity") (8 . "PLANTS") (62 . 94) (370 . 13) (100 . "AcDbPolyline") (90 . 2) (70 . 0)
(43 . 0.0) (10 15787.3300904977 289.5925339367) (10 15814.4796380091 294.1176470588))
((0 . "LWPOLYLINE") (100 . "AcDbEntity") (8 . "PLANTS") (62 . 94) (370 . 13) (100 . "AcDbPolyline") (90 . 2) (70 . 0)
(43 . 0.0) (10 15822.0192307692 6847.6618778281) (10 15788.0825791855 6840.1209276018))
((0 . "LWPOLYLINE") (100 . "AcDbEntity") (8 . "PLANTS") (62 . 94) (370 . 13) (100 . "AcDbPolyline") (90 . 2) (70 . 0)
(43 . 0.0) (10 15791.8552036199 361.9909502262) (10 15799.3947963801 361.9909502262))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15837.1040723982 6923.0769230769 0.0) (10 15817.6780294783 6918.0585714446 0.0) (10 15813.8675539481
6947.3894296128 0.0) (10 15795.6278280543 6945.7013574661 0.0))
((0 . "LWPOLYLINE") (100 . "AcDbEntity") (8 . "PLANTS") (62 . 94) (370 . 13) (100 . "AcDbPolyline") (90 . 2) (70 . 0)
(43 . 0.0) (10 15806.9400452489 4110.1059954751) (10 15795.6278280543 4083.7104072398))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7956005599) (40
. 1) (40 . 1) (40 . 1) (40 . 1) (10 15871.040723982 493.967760181 0.0) (10 15825.3129784776 476.8106064281 0.0) (10
15840.6337750838 402.3301253342 0.0) (10 15812.7001736165 364.2368509772 0.0) (10 15799.3947963801 361.9909502262 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15799.3947963801 241.3263574661 0.0) (10 15834.3391040477 227.3598290093 0.0) (10 15879.3368900046
220.411838465 0.0) (10 15912.5169683258 241.3263574661 0.0))
((0 . "LWPOLYLINE") (100 . "AcDbEntity") (8 . "PLANTS") (62 . 94) (370 . 13) (100 . "AcDbPolyline") (90 . 3) (70 . 0)
(43 . 0.0) (10 15848.4162895928 3831.0704751131) (10 15833.3314479638 3842.2287330317) (10 15803.1674208145
3842.3826923077))
((0 . "LWPOLYLINE") (100 . "AcDbEntity") (8 . "PLANTS") (62 . 94) (370 . 13) (100 . "AcDbPolyline") (90 . 2) (70 . 0)
(43 . 0.0) (10 15803.1674208145 3800.9049773756) (10 15803.1674208145 3842.3826923077))
((0 . "LWPOLYLINE") (100 . "AcDbEntity") (8 . "PLANTS") (62 . 94) (370 . 13) (100 . "AcDbPolyline") (90 . 3) (70 . 0)
(43 . 0.0) (10 15852.1889140272 3808.446040724) (10 15837.1040723982 3801.0596153846) (10 15803.1674208145
3800.9049773756))
((0 . "LWPOLYLINE") (100 . "AcDbEntity") (8 . "PLANTS") (62 . 94) (370 . 13) (100 . "AcDbPolyline") (90 . 3) (70 . 0)
(43 . 0.0) (10 15810.7070135747 7051.2817873303) (10 15837.1040723982 7046.4553167421) (10 15874.8133484163
7024.8868778281))
((0 . "LWPOLYLINE") (100 . "AcDbEntity") (8 . "PLANTS") (62 . 94) (370 . 13) (100 . "AcDbPolyline") (90 . 2) (70 . 0)
(43 . 0.0) (10 15814.4796380091 294.1176470588) (10 15844.6436651584 271.4932126697))
((0 . "LWPOLYLINE") (100 . "AcDbEntity") (8 . "PLANTS") (62 . 94) (370 . 13) (100 . "AcDbPolyline") (90 . 2) (70 . 0)
(43 . 0.0) (10 15814.4796380091 294.1176470588) (10 15871.0407239819 335.596719457))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5176544711) (40
. 1) (40 . 1) (40 . 1) (40 . 1) (10 15822.0192307692 6847.661877828 0.0) (10 15838.4599878667 6829.7027297104 0.0) (10
15876.905744687 6849.0829667159 0.0) (10 15916.7886450188 6844.478146662 0.0) (10 15935.1414027149 6847.661877828 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15822.0192307692 6847.6618778281 0.0) (10 15813.0576351294 6895.1395455116 0.0) (10 15888.4748317457
6882.1712943395 0.0) (10 15893.6651583711 6923.0769230769 0.0))
((0 . "LWPOLYLINE") (100 . "AcDbEntity") (8 . "PLANTS") (62 . 94) (370 . 13) (100 . "AcDbPolyline") (90 . 2) (70 . 0)
(43 . 0.0) (10 15829.564479638 1029.4117647059) (10 15834.8547453399 1027.1343311177))
((0 . "LWPOLYLINE") (100 . "AcDbEntity") (8 . "PLANTS") (62 . 94) (370 . 13) (100 . "AcDbPolyline") (90 . 2) (70 . 0)
(43 . 0.0) (10 15833.0556818199 4254.6798395736) (10 15833.3314479638 4177.9792986425))
((0 . "LWPOLYLINE") (100 . "AcDbEntity") (8 . "PLANTS") (62 . 94) (370 . 13) (100 . "AcDbPolyline") (90 . 3) (70 . 0)
(43 . 0.0) (10 15833.3314479638 4177.9792986425) (10 15859.7285067873 4178.1271493213) (10 15884.4771314119
4189.3979133614))
((0 . "LWPOLYLINE") (100 . "AcDbEntity") (8 . "PLANTS") (62 . 94) (370 . 13) (100 . "AcDbPolyline") (90 . 2) (70 . 0)
(43 . 0.0) (10 15895.5549484536 4150.6255537155) (10 15893.665158371 4147.8125565611))
((0 . "LWPOLYLINE") (100 . "AcDbEntity") (8 . "PLANTS") (62 . 94) (370 . 13) (100 . "AcDbPolyline") (90 . 2) (70 . 0)
(43 . 0.0) (10 15837.1040723982 4000.7537330317) (10 15833.3314479638 4012.0659502262))
((0 . "LWPOLYLINE") (100 . "AcDbEntity") (8 . "PLANTS") (62 . 94) (370 . 13) (100 . "AcDbPolyline") (90 . 2) (70 . 0)
(43 . 0.0) (10 15837.1040723982 4049.7737556561) (10 15833.3314479638 4012.0659502262))
((0 . "LWPOLYLINE") (100 . "AcDbEntity") (8 . "PLANTS") (62 . 94) (370 . 13) (100 . "AcDbPolyline") (90 . 2) (70 . 0)
(43 . 0.0) (10 15837.1040723982 4000.7537330317) (10 15833.3314479638 3985.6716063348))
((0 . "LWPOLYLINE") (100 . "AcDbEntity") (8 . "PLANTS") (62 . 94) (370 . 13) (100 . "AcDbPolyline") (90 . 2) (70 . 0)
(43 . 0.0) (10 15837.1040723982 7013.5746606335) (10 15859.7285067873 6990.9502262443))
((0 . "LWPOLYLINE") (100 . "AcDbEntity") (8 . "PLANTS") (62 . 94) (370 . 13) (100 . "AcDbPolyline") (90 . 2) (70 . 0)
(43 . 0.0) (10 15837.1040723982 4049.7737556561) (10 15837.1040723982 4091.2514705882))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15893.665158371 4147.8125565611 0.0) (10 15862.7862381631 4153.6693616638 0.0) (10 15821.6476649839
4127.43935645 0.0) (10 15837.1040723982 4091.2514705882 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15893.665158371 4147.8125565611 0.0) (10 15897.0704187128 4116.4477307152 0.0) (10 15870.8901022364
4082.7672430657 0.0) (10 15837.1040723982 4091.2514705882 0.0))
((0 . "LWPOLYLINE") (100 . "AcDbEntity") (8 . "PLANTS") (62 . 94) (370 . 13) (100 . "AcDbPolyline") (90 . 2) (70 . 0)
(43 . 0.0) (10 15837.1040723982 4049.7737556561) (10 15855.9558823529 4049.7737556561))
((0 . "LWPOLYLINE") (100 . "AcDbEntity") (8 . "PLANTS") (62 . 94) (370 . 13) (100 . "AcDbPolyline") (90 . 2) (70 . 0)
(43 . 0.0) (10 15859.7285067873 4004.5248868778) (10 15837.1040723982 4000.7537330317))
((0 . "LWPOLYLINE") (100 . "AcDbEntity") (8 . "PLANTS") (62 . 94) (370 . 13) (100 . "AcDbPolyline") (90 . 2) (70 . 0)
(43 . 0.0) (10 15852.1889140272 3808.446040724) (10 15848.4162895928 3831.0704751131))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15897.4377828054 3868.778280543 0.0) (10 15875.019456473 3871.1218693862 0.0) (10 15851.5430211613
3855.5095436494 0.0) (10 15848.4162895928 3831.0704751131 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16025.6391402716 6772.2476244344 0.0) (10 16002.4095195061 6705.6295258298 0.0) (10 15904.439705166
6744.5680717534 0.0) (10 15852.1889140272 6745.8519230769 0.0))
((0 . "LWPOLYLINE") (100 . "AcDbEntity") (8 . "PLANTS") (62 . 94) (370 . 13) (100 . "AcDbPolyline") (90 . 2) (70 . 0)
(43 . 0.0) (10 15855.9558823529 6779.7885746606) (10 15852.1889140272 6745.8519230769))
((0 . "LWPOLYLINE") (100 . "AcDbEntity") (8 . "PLANTS") (62 . 94) (370 . 13) (100 . "AcDbPolyline") (90 . 3) (70 . 0)
(43 . 0.0) (10 15852.1889140272 3808.446040724) (10 15871.0407239819 3797.282239819) (10 15927.6018099548
3799.0200226244))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15871.0407522624 957.767760181 0.0) (10 15863.7454598182 958.6150548022 0.0) (10 15852.4492571366
952.8708043644 0.0) (10 15852.1889140272 965.3082579186 0.0))
((0 . "LWPOLYLINE") (100 . "AcDbEntity") (8 . "PLANTS") (62 . 94) (370 . 13) (100 . "AcDbPolyline") (90 . 3) (70 . 0)
(43 . 0.0) (10 15855.9558823529 6779.7885746606) (10 15886.1255656109 6787.1820135747) (10 16006.7873303167
6787.3303167421))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15863.5011312217 403.4700226244 0.0) (10 15886.7091032862 390.928307921 0.0) (10 15874.809466145
352.2929780566 0.0) (10 15871.0407239819 335.596719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15871.0407239819 4049.7737556561 0.0) (10 15885.7449582377 4071.3041449032 0.0) (10 15876.132720334
4044.9835170616 0.0) (10 15886.1255656109 4049.7737556561 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15871.0407239818 493.967760181 0.0) (10 15916.4254186944 488.7741183073 0.0) (10 15898.9707535518
420.6095559323 0.0) (10 15916.2895927602 392.1578054299 0.0))
((0 . "LWPOLYLINE") (100 . "AcDbEntity") (8 . "PLANTS") (62 . 94) (370 . 13) (100 . "AcDbPolyline") (90 . 2) (70 . 0)
(43 . 0.0) (10 15874.8133484163 512.8195701357) (10 15871.0407239819 493.967760181))
((0 . "LWPOLYLINE") (100 . "AcDbEntity") (8 . "PLANTS") (62 . 94) (370 . 13) (100 . "AcDbPolyline") (90 . 2) (70 . 0)
(43 . 0.0) (10 15893.665158371 335.596719457) (10 15871.0407239819 335.596719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15965.3110859729 6998.4919683258 0.0) (10 15929.5780601213 6992.7581463444 0.0) (10 15911.8164178814
7038.90078696 0.0) (10 15874.8133484163 7024.8868778281 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15946.4536199095 6964.5553167421 0.0) (10 15927.5140216045 6980.5855691124 0.0) (10 15877.7391679339
6990.2315555792 0.0) (10 15874.8133484163 7024.8868778281 0.0))
((0 . "LWPOLYLINE") (100 . "AcDbEntity") (8 . "PLANTS") (62 . 94) (370 . 13) (100 . "AcDbPolyline") (90 . 2) (70 . 0)
(43 . 0.0) (10 15893.665158371 6923.0769230769) (10 15878.5803167421 6968.3257918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15937.0900356919 4026.8648181161 0.0) (10 15918.1039126564 4028.6048011816 0.0) (10 15899.3107353424
4018.1392757134 0.0) (10 15882.3529411765 4012.0659502262 0.0))
((0 . "LWPOLYLINE") (100 . "AcDbEntity") (8 . "PLANTS") (62 . 94) (370 . 13) (100 . "AcDbPolyline") (90 . 2) (70 . 0)
(43 . 0.0) (10 15901.2047511312 3944.1926470588) (10 15882.3529411765 3955.5048642534))
((0 . "LWPOLYLINE") (100 . "AcDbEntity") (8 . "PLANTS") (62 . 94) (370 . 13) (100 . "AcDbPolyline") (90 . 3) (70 . 0)
(43 . 0.0) (10 15912.5169683258 3981.9004524887) (10 15893.6720588235 3974.2044117647) (10 15882.3529411765
3955.5048642534))
((0 . "LWPOLYLINE") (100 . "AcDbEntity") (8 . "PLANTS") (62 . 94) (370 . 13) (100 . "AcDbPolyline") (90 . 2) (70 . 0)
(43 . 0.0) (10 15886.1255656109 554.2986425339) (10 15884.2329318131 560.2140474339))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15893.665158371 335.596719457 0.0) (10 15916.4940347932 316.7643049263 0.0) (10 15860.5643603228
275.8413782578 0.0) (10 15889.8925339367 267.7234162896 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15893.665158371 6923.0769230769 0.0) (10 15926.8421242498 6953.7955002987 0.0) (10 15959.9363451512
6906.0916194254 0.0) (10 15991.7024886878 6923.0769230769 0.0))
((0 . "LWPOLYLINE") (100 . "AcDbEntity") (8 . "PLANTS") (62 . 94) (370 . 13) (100 . "AcDbPolyline") (90 . 2) (70 . 0)
(43 . 0.0) (10 15893.665158371 335.596719457) (10 15920.0622171946 350.6787330317))
((0 . "LWPOLYLINE") (100 . "AcDbEntity") (8 . "PLANTS") (62 . 94) (370 . 13) (100 . "AcDbPolyline") (90 . 3) (70 . 0)
(43 . 0.0) (10 15897.4377828054 3868.778280543) (10 15905.1306561086 3849.925) (10 15923.8291855204 3834.8416289593))
((0 . "LWPOLYLINE") (100 . "AcDbEntity") (8 . "PLANTS") (62 . 94) (370 . 13) (100 . "AcDbPolyline") (90 . 2) (70 . 0)
(43 . 0.0) (10 15897.4377828054 3868.778280543) (10 15908.75 3895.1738687783))
((0 . "LWPOLYLINE") (100 . "AcDbEntity") (8 . "PLANTS") (62 . 94) (370 . 13) (100 . "AcDbPolyline") (90 . 2) (70 . 0)
(43 . 0.0) (10 15908.75 3914.0271493213) (10 15908.75 3895.1738687783))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15908.75 3914.0271493213 0.0) (10 15922.8270451881 3944.379690573 0.0) (10 15966.783080297
3921.6006142476 0.0) (10 15980.3902714932 3902.7149321268 0.0))
((0 . "LWPOLYLINE") (100 . "AcDbEntity") (8 . "PLANTS") (62 . 94) (370 . 13) (100 . "AcDbPolyline") (90 . 3) (70 . 0)
(43 . 0.0) (10 15965.3110859729 3865.0071266968) (10 15953.9904977376 3882.6634615385) (10 15908.75 3895.1738687783))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15987.935520362 248.8687782805 0.0) (10 15965.4983881315 238.3464207702 0.0) (10 15936.5427838954
230.7695908822 0.0) (10 15912.5169683258 241.3263574661 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15931.3744343891 350.6787330317 0.0) (10 15934.4567833163 313.3636669647 0.0) (10 15926.262714347
275.8516373266 0.0) (10 15912.5169683258 241.3263574661 0.0))
((0 . "LWPOLYLINE") (100 . "AcDbEntity") (8 . "PLANTS") (62 . 94) (370 . 13) (100 . "AcDbPolyline") (90 . 2) (70 . 0)
(43 . 0.0) (10 15916.2895927602 392.1578054299) (10 15935.1414027149 392.1578054299))
((0 . "LWPOLYLINE") (100 . "AcDbEntity") (8 . "PLANTS") (62 . 94) (370 . 13) (100 . "AcDbPolyline") (90 . 2) (70 . 0)
(43 . 0.0) (10 15916.2895927602 392.1578054299) (10 15920.0622171946 350.6787330317))
((0 . "LWPOLYLINE") (100 . "AcDbEntity") (8 . "PLANTS") (62 . 94) (370 . 13) (100 . "AcDbPolyline") (90 . 2) (70 . 0)
(43 . 0.0) (10 15931.3744343891 350.6787330317) (10 15920.0622171946 350.6787330317))
((0 . "LWPOLYLINE") (100 . "AcDbEntity") (8 . "PLANTS") (62 . 94) (370 . 13) (100 . "AcDbPolyline") (90 . 2) (70 . 0)
(43 . 0.0) (10 15923.8291855204 3963.0471719457) (10 15942.6866515837 3966.817081448))
((0 . "LWPOLYLINE") (100 . "AcDbEntity") (8 . "PLANTS") (62 . 94) (370 . 13) (100 . "AcDbPolyline") (90 . 3) (70 . 0)
(43 . 0.0) (10 15927.6018099548 3799.0200226244) (10 15923.9783936652 3808.3790723982) (10 15923.8291855204
3834.8416289593))
((0 . "LWPOLYLINE") (100 . "AcDbEntity") (8 . "PLANTS") (62 . 94) (370 . 13) (100 . "AcDbPolyline") (90 . 3) (70 . 0)
(43 . 0.0) (10 15953.9988687783 3849.925) (10 15935.1414027149 3844.9562217195) (10 15923.8291855204 3834.8416289593))
((0 . "LWPOLYLINE") (100 . "AcDbEntity") (8 . "PLANTS") (62 . 94) (370 . 13) (100 . "AcDbPolyline") (90 . 3) (70 . 0)
(43 . 0.0) (10 15927.6018099548 3799.0200226244) (10 15932.4294117647 3774.5093891403) (10 15950.2262443439
3759.4272624434))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15999.2644099786 3793.4377304122 0.0) (10 15974.9126139363 3791.0906034346 0.0) (10 15952.0857955931
3806.9444314868 0.0) (10 15927.6018099548 3799.0200226244 0.0))
((0 . "LWPOLYLINE") (100 . "AcDbEntity") (8 . "PLANTS") (62 . 94) (370 . 13) (100 . "AcDbPolyline") (90 . 2) (70 . 0)
(43 . 0.0) (10 15931.3744343891 350.6787330317) (10 15946.4536199095 369.5333710407))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15935.141402715 6847.6618778281 0.0) (10 15967.9156181793 6834.5148773336 0.0) (10 16025.2117182672
6830.789562053 0.0) (10 16033.1843891403 6874.0575791855 0.0))
((0 . "LWPOLYLINE") (100 . "AcDbEntity") (8 . "PLANTS") (62 . 94) (370 . 13) (100 . "AcDbPolyline") (90 . 3) (70 . 0)
(43 . 0.0) (10 15957.7658371041 6889.1402714932) (10 15947.5114253394 6877.8280542986) (10 15935.1414027149
6847.6618778281))
((0 . "LWPOLYLINE") (100 . "AcDbEntity") (8 . "PLANTS") (62 . 94) (370 . 13) (100 . "AcDbPolyline") (90 . 2) (70 . 0)
(43 . 0.0) (10 15935.1414027149 392.1578054299) (10 15946.4536199095 369.5333710407))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4058016484) (40
. 1) (40 . 1) (40 . 1) (40 . 1) (10 15935.141402715 392.1578054298 0.0) (10 15942.9939932512 403.0926435431 0.0) (10
15939.322341686 437.4574968551 0.0) (10 15968.5115033098 461.8386979878 0.0) (10 15965.3110859729 482.6555429864 0.0))
((0 . "LWPOLYLINE") (100 . "AcDbEntity") (8 . "PLANTS") (62 . 94) (370 . 13) (100 . "AcDbPolyline") (90 . 2) (70 . 0)
(43 . 0.0) (10 15976.6233031674 380.8455882353) (10 15946.4536199095 369.5333710407))
((0 . "LWPOLYLINE") (100 . "AcDbEntity") (8 . "PLANTS") (62 . 94) (370 . 13) (100 . "AcDbPolyline") (90 . 2) (70 . 0)
(43 . 0.0) (10 15953.9988687783 3849.925) (10 15961.5384615385 3846.1538461538))
((0 . "LWPOLYLINE") (100 . "AcDbEntity") (8 . "PLANTS") (62 . 94) (370 . 13) (100 . "AcDbPolyline") (90 . 2) (70 . 0)
(43 . 0.0) (10 15953.9988687783 3849.925) (10 15965.3110859729 3865.0071266968))
((0 . "LWPOLYLINE") (100 . "AcDbEntity") (8 . "PLANTS") (62 . 94) (370 . 13) (100 . "AcDbPolyline") (90 . 2) (70 . 0)
(43 . 0.0) (10 15965.3110859729 6998.4919683258) (10 15972.850678733 6994.7207013575))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4776036651)
(40 . 0.5786222062) (40 . 1) (40 . 1) (40 . 1) (40 . 1) (10 16036.951357466 7013.5746606335 0.0) (10 16003.1668692217
7020.1852621343 0.0) (10 15979.6311248235 7075.0076171813 0.0) (10 15899.9599481212 7085.8644586737 0.0) (10
15948.1975277369 6981.4563335063 0.0) (10 15965.3110859729 6998.4919683258 0.0))
((0 . "LWPOLYLINE") (100 . "AcDbEntity") (8 . "PLANTS") (62 . 94) (370 . 13) (100 . "AcDbPolyline") (90 . 3) (70 . 0)
(43 . 0.0) (10 16013.2866567761 3849.5267176022) (10 15991.7024886878 3863.9510180995) (10 15965.3110859729
3865.0071266968))
((0 . "LWPOLYLINE") (100 . "AcDbEntity") (8 . "PLANTS") (62 . 94) (370 . 13) (100 . "AcDbPolyline") (90 . 3) (70 . 0)
(43 . 0.0) (10 16063.3484162896 6938.1596153846) (10 16003.0147058824 6985.9885746606) (10 15972.850678733
6994.7207013575))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15991.7024886878 6923.0769230769 0.0) (10 15992.1792332408 6949.4370689364 0.0) (10 15959.2756645016
6967.6905300866 0.0) (10 15972.850678733 6994.7207013575 0.0))
((0 . "LWPOLYLINE") (100 . "AcDbEntity") (8 . "PLANTS") (62 . 94) (370 . 13) (100 . "AcDbPolyline") (90 . 2) (70 . 0)
(43 . 0.0) (10 15976.6233031674 380.8455882353) (10 16006.7873303167 380.8455882353))
((0 . "LWPOLYLINE") (100 . "AcDbEntity") (8 . "PLANTS") (62 . 94) (370 . 13) (100 . "AcDbPolyline") (90 . 3) (70 . 0)
(43 . 0.0) (10 15976.6233031674 380.8455882353) (10 15977.678280543 407.2398190045) (10 15991.7024886878
429.8642533937))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15987.935520362 248.8687782805 0.0) (10 16006.5176730351 226.818018184 0.0) (10 16038.7878515847
228.0442336239 0.0) (10 16063.3484162896 237.556561086 0.0))
((0 . "LWPOLYLINE") (100 . "AcDbEntity") (8 . "PLANTS") (62 . 94) (370 . 13) (100 . "AcDbPolyline") (90 . 3) (70 . 0)
(43 . 0.0) (10 15987.935520362 248.8687782805) (10 15988.9904977376 263.9459276018) (10 15995.4751131222
271.4932126697))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16029.4117647059 6900.4524886878 0.0) (10 16004.4603328901 6887.7742167672 0.0) (10 16009.2274074806
6919.8383892608 0.0) (10 15991.7024886878 6923.0769230769 0.0))
((0 . "LWPOLYLINE") (100 . "AcDbEntity") (8 . "PLANTS") (62 . 94) (370 . 13) (100 . "AcDbPolyline") (90 . 3) (70 . 0)
(43 . 0.0) (10 15991.7024886878 429.8642533937) (10 16003.0147058824 428.6593891403) (10 16014.3269230769
418.5520361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 15991.7024886878 429.8642533937 0.0) (10 15984.3250136884 442.4438151082 0.0) (10 15994.4487781887
479.520422694 0.0) (10 16014.3269230769 467.5707013575 0.0))
((0 . "LWPOLYLINE") (100 . "AcDbEntity") (8 . "PLANTS") (62 . 94) (370 . 13) (100 . "AcDbPolyline") (90 . 2) (70 . 0)
(43 . 0.0) (10 16033.1843891403 6568.6277149321) (10 16001.9490774457 6584.2441526631))
((0 . "LWPOLYLINE") (100 . "AcDbEntity") (8 . "PLANTS") (62 . 94) (370 . 13) (100 . "AcDbPolyline") (90 . 2) (70 . 0)
(43 . 0.0) (10 15995.4751131222 271.4932126697) (10 16003.0147058824 305.4298642534))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16048.2635746606 309.1996606335 0.0) (10 16052.0512254946 276.3555602899 0.0) (10 16018.8801782513
265.424317274 0.0) (10 15995.4751131222 271.4932126697 0.0))
((0 . "LWPOLYLINE") (100 . "AcDbEntity") (8 . "PLANTS") (62 . 94) (370 . 13) (100 . "AcDbPolyline") (90 . 3) (70 . 0)
(43 . 0.0) (10 16012.9551851777 6486.0358067468) (10 16078.4332579186 6487.7771493213) (10 16089.7454751131
6493.2126696833))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16036.9513574661 6677.9786199095 0.0) (10 16020.3423822047 6650.5221380123 0.0) (10 15963.3398531437
6662.9439994416 0.0) (10 16003.0147058824 6700.6030542986 0.0))
((0 . "LWPOLYLINE") (100 . "AcDbEntity") (8 . "PLANTS") (62 . 94) (370 . 13) (100 . "AcDbPolyline") (90 . 3) (70 . 0)
(43 . 0.0) (10 16003.0147058824 305.4298642534) (10 16007.8436651584 328.0542986425) (10 16021.8721719457
358.2211538462))
((0 . "LWPOLYLINE") (100 . "AcDbEntity") (8 . "PLANTS") (62 . 94) (370 . 13) (100 . "AcDbPolyline") (90 . 2) (70 . 0)
(43 . 0.0) (10 16048.2635746606 309.1996606335) (10 16003.0147058824 305.4298642534))
((0 . "LWPOLYLINE") (100 . "AcDbEntity") (8 . "PLANTS") (62 . 94) (370 . 13) (100 . "AcDbPolyline") (90 . 3) (70 . 0)
(43 . 0.0) (10 16025.6391402715 6772.2476244344) (10 16010.7132352941 6780.8384615385) (10 16006.7873303167
6787.3303167421))
((0 . "LWPOLYLINE") (100 . "AcDbEntity") (8 . "PLANTS") (62 . 94) (370 . 13) (100 . "AcDbPolyline") (90 . 2) (70 . 0)
(43 . 0.0) (10 16006.7873303167 6787.3303167421) (10 16018.0995475113 6806.1842760181))
((0 . "LWPOLYLINE") (100 . "AcDbEntity") (8 . "PLANTS") (62 . 94) (370 . 13) (100 . "AcDbPolyline") (90 . 2) (70 . 0)
(43 . 0.0) (10 16021.8721719457 358.2211538462) (10 16006.7873303167 380.8455882353))
((0 . "LWPOLYLINE") (100 . "AcDbEntity") (8 . "PLANTS") (62 . 94) (370 . 13) (100 . "AcDbPolyline") (90 . 2) (70 . 0)
(43 . 0.0) (10 16014.3269230769 418.5520361991) (10 16006.7873303167 380.8455882353))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16101.0576923077 448.7188914027 0.0) (10 16067.4580954442 451.9193339869 0.0) (10 16047.2285095794
417.8384177379 0.0) (10 16014.3269230769 418.5520361991 0.0))
((0 . "LWPOLYLINE") (100 . "AcDbEntity") (8 . "PLANTS") (62 . 94) (370 . 13) (100 . "AcDbPolyline") (90 . 2) (70 . 0)
(43 . 0.0) (10 16018.0995475113 3898.9437782805) (10 16025.1382229718 3896.932982385))
((0 . "LWPOLYLINE") (100 . "AcDbEntity") (8 . "PLANTS") (62 . 94) (370 . 13) (100 . "AcDbPolyline") (90 . 2) (70 . 0)
(43 . 0.0) (10 16070.8880090498 373.3031674208) (10 16021.8721719457 358.2211538462))
((0 . "LWPOLYLINE") (100 . "AcDbEntity") (8 . "PLANTS") (62 . 94) (370 . 13) (100 . "AcDbPolyline") (90 . 3) (70 . 0)
(43 . 0.0) (10 16025.6391402715 6772.2476244344) (10 16044.4966063348 6772.3954751131) (10 16089.7454751131
6785.4446832579))
((0 . "LWPOLYLINE") (100 . "AcDbEntity") (8 . "PLANTS") (62 . 94) (370 . 13) (100 . "AcDbPolyline") (90 . 2) (70 . 0)
(43 . 0.0) (10 16029.4117647059 6900.4524886878) (10 16033.1843891403 6874.0575791855))
((0 . "LWPOLYLINE") (100 . "AcDbEntity") (8 . "PLANTS") (62 . 94) (370 . 13) (100 . "AcDbPolyline") (90 . 3) (70 . 0)
(43 . 0.0) (10 16063.3484162896 6938.1596153846) (10 16050.9798642534 6915.6834841629) (10 16029.4117647059
6900.4524886878))
((0 . "LWPOLYLINE") (100 . "AcDbEntity") (8 . "PLANTS") (62 . 94) (370 . 13) (100 . "AcDbPolyline") (90 . 3) (70 . 0)
(43 . 0.0) (10 16033.1843891403 6874.0575791855) (10 16085.9728506787 6873.9092760181) (10 16101.0576923077
6870.2863122172))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16033.1843891403 6568.6277149321 0.0) (10 16037.6370693735 6563.3204607271 0.0) (10 16022.2185764032
6618.865059223 0.0) (10 16044.4966063348 6613.8765837104 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16033.1843891403 6568.6277149321 0.0) (10 16058.4108380909 6566.9118209186 0.0) (10 16061.8071767596
6601.7138146094 0.0) (10 16044.4966063348 6613.8765837104 0.0))
((0 . "LWPOLYLINE") (100 . "AcDbEntity") (8 . "PLANTS") (62 . 94) (370 . 13) (100 . "AcDbPolyline") (90 . 2) (70 . 0)
(43 . 0.0) (10 16036.9513574661 6677.9786199095) (10 16052.036199095 6677.9786199095))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16036.9513574661 6677.9786199095 0.0) (10 16029.0192936508 6689.0704872822 0.0) (10 16029.3349243042
6711.7176912598 0.0) (10 16048.2635746606 6711.9152714932 0.0))
((0 . "LWPOLYLINE") (100 . "AcDbEntity") (8 . "PLANTS") (62 . 94) (370 . 13) (100 . "AcDbPolyline") (90 . 2) (70 . 0)
(43 . 0.0) (10 16059.5757918552 6647.8132352941) (10 16044.4966063348 6613.8765837104))
((0 . "LWPOLYLINE") (100 . "AcDbEntity") (8 . "PLANTS") (62 . 94) (370 . 13) (100 . "AcDbPolyline") (90 . 3) (70 . 0)
(43 . 0.0) (10 16052.036199095 6677.9786199095) (10 16055.6527149321 6693.0621040724) (10 16048.2635746606
6711.9152714932))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16048.2635746606 6711.9152714932 0.0) (10 16045.7923439869 6730.3317337312 0.0) (10 16066.1912441506
6749.9535221709 0.0) (10 16085.9728506787 6738.3109728507 0.0))
((0 . "LWPOLYLINE") (100 . "AcDbEntity") (8 . "PLANTS") (62 . 94) (370 . 13) (100 . "AcDbPolyline") (90 . 2) (70 . 0)
(43 . 0.0) (10 16048.2635746606 309.1996606335) (10 16070.8880090498 316.742081448))
((0 . "LWPOLYLINE") (100 . "AcDbEntity") (8 . "PLANTS") (62 . 94) (370 . 13) (100 . "AcDbPolyline") (90 . 3) (70 . 0)
(43 . 0.0) (10 16052.036199095 7021.1164027149) (10 16053.2403846154 7006.032918552) (10 16067.121040724
6990.9502262443))
((0 . "LWPOLYLINE") (100 . "AcDbEntity") (8 . "PLANTS") (62 . 94) (370 . 13) (100 . "AcDbPolyline") (90 . 3) (70 . 0)
(43 . 0.0) (10 16059.5757918552 6647.8132352941) (10 16053.0925339367 6662.8959276018) (10 16052.036199095
6677.9786199095))
((0 . "LWPOLYLINE") (100 . "AcDbEntity") (8 . "PLANTS") (62 . 94) (370 . 13) (100 . "AcDbPolyline") (90 . 3) (70 . 0)
(43 . 0.0) (10 16055.8088235294 7062.5940045249) (10 16078.4332579186 7044.9317873303) (10 16101.0576923077
7039.9695701357))
((0 . "LWPOLYLINE") (100 . "AcDbEntity") (8 . "PLANTS") (62 . 94) (370 . 13) (100 . "AcDbPolyline") (90 . 2) (70 . 0)
(43 . 0.0) (10 16089.7454751131 6647.8132352941) (10 16059.5757918552 6647.8132352941))
((0 . "LWPOLYLINE") (100 . "AcDbEntity") (8 . "PLANTS") (62 . 94) (370 . 13) (100 . "AcDbPolyline") (90 . 2) (70 . 0)
(43 . 0.0) (10 16063.3484162896 6938.1596153846) (10 16078.4332579186 6941.9308823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16138.7613122172 248.8687782805 0.0) (10 16120.668621383 228.790386211 0.0) (10 16086.575667408
224.0270692457 0.0) (10 16063.3484162896 237.556561086 0.0))
((0 . "LWPOLYLINE") (100 . "AcDbEntity") (8 . "PLANTS") (62 . 94) (370 . 13) (100 . "AcDbPolyline") (90 . 2) (70 . 0)
(43 . 0.0) (10 16063.3484162896 237.556561086) (10 16074.6606334842 271.4932126697))
((0 . "LWPOLYLINE") (100 . "AcDbEntity") (8 . "PLANTS") (62 . 94) (370 . 13) (100 . "AcDbPolyline") (90 . 2) (70 . 0)
(43 . 0.0) (10 16070.8880090498 373.3031674208) (10 16119.9095022624 373.3031674208))
((0 . "LWPOLYLINE") (100 . "AcDbEntity") (8 . "PLANTS") (62 . 94) (370 . 13) (100 . "AcDbPolyline") (90 . 2) (70 . 0)
(43 . 0.0) (10 16070.8880090498 373.3031674208) (10 16070.8880090498 316.742081448))
((0 . "LWPOLYLINE") (100 . "AcDbEntity") (8 . "PLANTS") (62 . 94) (370 . 13) (100 . "AcDbPolyline") (90 . 2) (70 . 0)
(43 . 0.0) (10 16085.9728506787 316.742081448) (10 16070.8880090498 316.742081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16078.4332579186 6941.9308823529 0.0) (10 16101.1095232015 6939.3660041373 0.0) (10 16131.5104950152
6924.0100167851 0.0) (10 16153.8461538462 6938.1596153846 0.0))
((0 . "LWPOLYLINE") (100 . "AcDbEntity") (8 . "PLANTS") (62 . 94) (370 . 13) (100 . "AcDbPolyline") (90 . 2) (70 . 0)
(43 . 0.0) (10 16082.2002262443 6964.5553167421) (10 16078.4332579186 6941.9308823529))
((0 . "LWPOLYLINE") (100 . "AcDbEntity") (8 . "PLANTS") (62 . 94) (370 . 13) (100 . "AcDbPolyline") (90 . 2) (70 . 0)
(43 . 0.0) (10 16078.4332579186 6417.7979638009) (10 16089.7454751131 6447.963800905))
((0 . "LWPOLYLINE") (100 . "AcDbEntity") (8 . "PLANTS") (62 . 94) (370 . 13) (100 . "AcDbPolyline") (90 . 2) (70 . 0)
(43 . 0.0) (10 16078.4332579186 6334.8416289593) (10 16089.7454751131 6353.6952488688))
((0 . "LWPOLYLINE") (100 . "AcDbEntity") (8 . "PLANTS") (62 . 94) (370 . 13) (100 . "AcDbPolyline") (90 . 2) (70 . 0)
(43 . 0.0) (10 16093.5124434389 6719.4570135747) (10 16085.9728506787 6738.3109728507))
((0 . "LWPOLYLINE") (100 . "AcDbEntity") (8 . "PLANTS") (62 . 94) (370 . 13) (100 . "AcDbPolyline") (90 . 2) (70 . 0)
(43 . 0.0) (10 16089.7454751131 6785.4446832579) (10 16085.9728506787 6738.3109728507))
((0 . "LWPOLYLINE") (100 . "AcDbEntity") (8 . "PLANTS") (62 . 94) (370 . 13) (100 . "AcDbPolyline") (90 . 3) (70 . 0)
(43 . 0.0) (10 16085.9728506787 316.742081448) (10 16097.2919683258 294.2660633484) (10 16134.9943438914
275.2630090498))
((0 . "LWPOLYLINE") (100 . "AcDbEntity") (8 . "PLANTS") (62 . 94) (370 . 13) (100 . "AcDbPolyline") (90 . 3) (70 . 0)
(43 . 0.0) (10 16085.9728506787 316.742081448) (10 16097.2850678733 324.1291855204) (10 16131.221719457 328.0542986425))
((0 . "LWPOLYLINE") (100 . "AcDbEntity") (8 . "PLANTS") (62 . 94) (370 . 13) (100 . "AcDbPolyline") (90 . 3) (70 . 0)
(43 . 0.0) (10 16138.7613122172 6779.7885746606) (10 16108.5972850679 6779.9368778281) (10 16089.7454751131
6785.4446832579))
((0 . "LWPOLYLINE") (100 . "AcDbEntity") (8 . "PLANTS") (62 . 94) (370 . 13) (100 . "AcDbPolyline") (90 . 3) (70 . 0)
(43 . 0.0) (10 16089.7454751131 6785.4446832579) (10 16089.8918552036 6825.0374434389) (10 16101.0576923077
6870.2863122172))
((0 . "LWPOLYLINE") (100 . "AcDbEntity") (8 . "PLANTS") (62 . 94) (370 . 13) (100 . "AcDbPolyline") (90 . 2) (70 . 0)
(43 . 0.0) (10 16089.7454751131 6685.520361991) (10 16093.5124434389 6719.4570135747))
((0 . "LWPOLYLINE") (100 . "AcDbEntity") (8 . "PLANTS") (62 . 94) (370 . 13) (100 . "AcDbPolyline") (90 . 2) (70 . 0)
(43 . 0.0) (10 16089.7454751131 6647.8132352941) (10 16127.4490950226 6647.8132352941))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16089.7454751131 6647.8132352941 0.0) (10 16062.0009851663 6601.2096149835 0.0) (10 16155.6177410055
6599.4824572692 0.0) (10 16127.4490950226 6647.8132352941 0.0))
((0 . "LWPOLYLINE") (100 . "AcDbEntity") (8 . "PLANTS") (62 . 94) (370 . 13) (100 . "AcDbPolyline") (90 . 2) (70 . 0)
(43 . 0.0) (10 16121.7929864253 6487.556561086) (10 16089.7454751131 6493.2126696833))
((0 . "LWPOLYLINE") (100 . "AcDbEntity") (8 . "PLANTS") (62 . 94) (370 . 13) (100 . "AcDbPolyline") (90 . 3) (70 . 0)
(43 . 0.0) (10 16093.5124434389 6508.2957013575) (10 16093.5124434389 6496.9834841629) (10 16089.7454751131
6493.2126696833))
((0 . "LWPOLYLINE") (100 . "AcDbEntity") (8 . "PLANTS") (62 . 94) (370 . 13) (100 . "AcDbPolyline") (90 . 2) (70 . 0)
(43 . 0.0) (10 16116.1368778281 6719.4570135747) (10 16093.5124434389 6719.4570135747))
((0 . "LWPOLYLINE") (100 . "AcDbEntity") (8 . "PLANTS") (62 . 94) (370 . 13) (100 . "AcDbPolyline") (90 . 2) (70 . 0)
(43 . 0.0) (10 16097.2850678733 6557.3154977376) (10 16123.6821266968 6557.3154977376))
((0 . "LWPOLYLINE") (100 . "AcDbEntity") (8 . "PLANTS") (62 . 94) (370 . 13) (100 . "AcDbPolyline") (90 . 2) (70 . 0)
(43 . 0.0) (10 16101.0576923077 7024.8868778281) (10 16101.0576923077 7039.9695701357))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4927641529)
(40 . 0.5764861589) (40 . 1) (40 . 1) (40 . 1) (40 . 1) (10 16138.7613122172 7058.8235294118 0.0) (10 16150.4729065341
7081.0009908214 0.0) (10 16107.9358091081 7104.3294068861 0.0) (10 16090.8299310654 7084.8240487517 0.0) (10
16108.4520712671 7053.089733378 0.0) (10 16101.0576923077 7039.9695701358 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16101.0576923077 7024.8868778281 0.0) (10 16135.8649380468 7028.725085092 0.0) (10 16169.2363935077
6985.7342557877 0.0) (10 16153.8461538462 6953.2430995475 0.0))
((0 . "LWPOLYLINE") (100 . "AcDbEntity") (8 . "PLANTS") (62 . 94) (370 . 13) (100 . "AcDbPolyline") (90 . 2) (70 . 0)
(43 . 0.0) (10 16101.0576923077 7024.8868778281) (10 16101.0576923077 7006.032918552))
((0 . "LWPOLYLINE") (100 . "AcDbEntity") (8 . "PLANTS") (62 . 94) (370 . 13) (100 . "AcDbPolyline") (90 . 3) (70 . 0)
(43 . 0.0) (10 16123.6821266968 6975.8675339367) (10 16118.7053167421 6994.5731900452) (10 16101.0576923077
7006.032918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16123.6821266969 6975.8675339367 0.0) (10 16105.768355064 6964.1202063924 0.0) (10 16079.4835121468
6992.2205567935 0.0) (10 16101.0576923077 7006.0329185521 0.0))
((0 . "LWPOLYLINE") (100 . "AcDbEntity") (8 . "PLANTS") (62 . 94) (370 . 13) (100 . "AcDbPolyline") (90 . 2) (70 . 0)
(43 . 0.0) (10 16146.306561086 6874.0575791855) (10 16101.0576923077 6870.2863122172))
((0 . "LWPOLYLINE") (100 . "AcDbEntity") (8 . "PLANTS") (62 . 94) (370 . 13) (100 . "AcDbPolyline") (90 . 3) (70 . 0)
(43 . 0.0) (10 16101.0576923077 448.7188914027) (10 16112.3699095023 448.7188914027) (10 16116.1368778281
452.4886877828))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16101.0576923077 448.7188914027 0.0) (10 16082.5764503516 414.259048346 0.0) (10 16120.7256269502
411.0866290311 0.0) (10 16131.2217194571 392.1578054299 0.0))
((0 . "LWPOLYLINE") (100 . "AcDbEntity") (8 . "PLANTS") (62 . 94) (370 . 13) (100 . "AcDbPolyline") (90 . 2) (70 . 0)
(43 . 0.0) (10 16112.3699095023 6297.1341628959) (10 16116.1368778281 6266.9683257919))
((0 . "LWPOLYLINE") (100 . "AcDbEntity") (8 . "PLANTS") (62 . 94) (370 . 13) (100 . "AcDbPolyline") (90 . 2) (70 . 0)
(43 . 0.0) (10 16127.4490950226 6696.8325791855) (10 16116.1368778281 6719.4570135747))
((0 . "LWPOLYLINE") (100 . "AcDbEntity") (8 . "PLANTS") (62 . 94) (370 . 13) (100 . "AcDbPolyline") (90 . 2) (70 . 0)
(43 . 0.0) (10 16116.1368778281 6719.4570135747) (10 16134.9943438914 6734.5397058824))
((0 . "SPLINE") (100 . "AcDbEntity") (8 . "PLANTS") (62 . 94) (370 . 13) (100 . "AcDbSpline") (70 . 0) (71 . 3) (72 .
13) (73 . 9) (74 . 0) (42 . 0.0000001) (43 . 0.0000001) (40 . 0.0) (40 . 0.0) (40 . 0.0) (40 . 0.0) (40 . 0.2194265697)
(40 . 0.3135419313) (40 . 0.3693960568) (40 . 0.5493292449) (40 . 0.8207421291) (40 . 1) (40 . 1) (40 . 1) (40 . 1) (10
16121.7929864253 6487.556561086 0.0) (10 16108.4700768404 6473.7158727077 0.0) (10 16131.312204671 6452.2910801614 0.0)
(10 16121.5141952933 6428.0896097612 0.0) (10 16123.2168656515 6405.6888147344 0.0) (10 16105.9293193403 6365.3018096274
0.0) (10 16173.6740295137 6343.8548875916 0.0) (10 16126.8857315612 6306.1198136336 0.0) (10 16116.1368778281
6331.0708144796 0.0))
((0 . "LWPOLYLINE") (100 . "AcDbEntity") (8 . "PLANTS") (62 . 94) (370 . 13) (100 . "AcDbPolyline") (90 . 2) (70 . 0)
(43 . 0.0) (10 16119.9095022624 6206.6364253394) (10 16119.9095022624 6236.8024886878))
((0 . "LWPOLYLINE") (100 . "AcDbEntity") (8 . "PLANTS") (62 . 94) (370 . 13) (100 . "AcDbPolyline") (90 . 3) (70 . 0)
(43 . 0.0) (10 16131.221719457 328.0542986425) (10 16131.068438914 350.6787330317) (10 16119.9095022624 373.3031674208))
((0 . "LWPOLYLINE") (100 . "AcDbEntity") (8 . "PLANTS") (62 . 94) (370 . 13) (100 . "AcDbPolyline") (90 . 2) (70 . 0)
(43 . 0.0) (10 16131.221719457 392.1578054299) (10 16119.9095022624 373.3031674208))
((0 . "LWPOLYLINE") (100 . "AcDbEntity") (8 . "PLANTS") (62 . 94) (370 . 13) (100 . "AcDbPolyline") (90 . 3) (70 . 0)
(43 . 0.0) (10 16121.7929864253 6487.556561086) (10 16126.253280543 6546.0029411765) (10 16123.6821266968
6557.3154977376))
((0 . "LWPOLYLINE") (100 . "AcDbEntity") (8 . "PLANTS") (62 . 94) (370 . 13) (100 . "AcDbPolyline") (90 . 2) (70 . 0)
(43 . 0.0) (10 16121.7929864253 6487.556561086) (10 16150.0735294118 6489.4418552036))
((0 . "LWPOLYLINE") (100 . "AcDbEntity") (8 . "PLANTS") (62 . 94) (370 . 13) (100 . "AcDbPolyline") (90 . 2) (70 . 0)
(43 . 0.0) (10 16123.6821266968 6975.8675339367) (10 16153.8461538462 6953.2430995475))
((0 . "LWPOLYLINE") (100 . "AcDbEntity") (8 . "PLANTS") (62 . 94) (370 . 13) (100 . "AcDbPolyline") (90 . 2) (70 . 0)
(43 . 0.0) (10 16123.6821266968 6564.8564479638) (10 16123.6821266968 6576.1686651584))
((0 . "LWPOLYLINE") (100 . "AcDbEntity") (8 . "PLANTS") (62 . 94) (370 . 13) (100 . "AcDbPolyline") (90 . 2) (70 . 0)
(43 . 0.0) (10 16123.6821266968 6564.8564479638) (10 16123.6821266968 6557.3154977376))
((0 . "LWPOLYLINE") (100 . "AcDbEntity") (8 . "PLANTS") (62 . 94) (370 . 13) (100 . "AcDbPolyline") (90 . 2) (70 . 0)
(43 . 0.0) (10 16123.6821266968 6564.8564479638) (10 16157.6187782805 6572.3981900452))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16127.4490950226 6696.8325791855 0.0) (10 16150.49383262 6692.7109157814 0.0) (10 16187.5678354954
6686.0793140365 0.0) (10 16202.8676470588 6711.9152714932 0.0))
((0 . "LWPOLYLINE") (100 . "AcDbEntity") (8 . "PLANTS") (62 . 94) (370 . 13) (100 . "AcDbPolyline") (90 . 3) (70 . 0)
(43 . 0.0) (10 16127.4490950226 6696.8325791855) (10 16123.6821266968 6677.9786199095) (10 16127.4490950226
6647.8132352941))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6514352421) (40
. 1) (40 . 1) (40 . 1) (40 . 1) (10 16127.4490950226 6647.8132352941 0.0) (10 16148.8005245093 6650.9175386766 0.0) (10
16173.6322174973 6630.597973901 0.0) (10 16181.8023761688 6601.4219284631 0.0) (10 16187.7828054297 6595.0226244343
0.0))
((0 . "LWPOLYLINE") (100 . "AcDbEntity") (8 . "PLANTS") (62 . 94) (370 . 13) (100 . "AcDbPolyline") (90 . 2) (70 . 0)
(43 . 0.0) (10 16146.306561086 392.1578054299) (10 16131.221719457 392.1578054299))
((0 . "LWPOLYLINE") (100 . "AcDbEntity") (8 . "PLANTS") (62 . 94) (370 . 13) (100 . "AcDbPolyline") (90 . 2) (70 . 0)
(43 . 0.0) (10 16150.0735294118 320.5118778281) (10 16131.221719457 328.0542986425))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16202.8676470588 6711.9152714932 0.0) (10 16193.6870133157 6737.65623556 0.0) (10 16153.3330547059
6734.4894639114 0.0) (10 16134.9943438914 6734.5397058824 0.0))
((0 . "LWPOLYLINE") (100 . "AcDbEntity") (8 . "PLANTS") (62 . 94) (370 . 13) (100 . "AcDbPolyline") (90 . 2) (70 . 0)
(43 . 0.0) (10 16138.7613122172 6779.7885746606) (10 16134.9943438914 6734.5397058824))
((0 . "LWPOLYLINE") (100 . "AcDbEntity") (8 . "PLANTS") (62 . 94) (370 . 13) (100 . "AcDbPolyline") (90 . 2) (70 . 0)
(43 . 0.0) (10 16138.7613122172 248.8687782805) (10 16134.9943438914 275.2630090498))
((0 . "LWPOLYLINE") (100 . "AcDbEntity") (8 . "PLANTS") (62 . 94) (370 . 13) (100 . "AcDbPolyline") (90 . 3) (70 . 0)
(43 . 0.0) (10 16150.0735294118 320.5118778281) (10 16141.3381221719 282.8123303167) (10 16134.9943438914
275.2630090498))
((0 . "LWPOLYLINE") (100 . "AcDbEntity") (8 . "PLANTS") (62 . 94) (370 . 13) (100 . "AcDbPolyline") (90 . 3) (70 . 0)
(43 . 0.0) (10 16138.7613122172 6779.7885746606) (10 16150.0735294118 6779.7885746606) (10 16153.8461538462
6783.559841629))
((0 . "LWPOLYLINE") (100 . "AcDbEntity") (8 . "PLANTS") (62 . 94) (370 . 13) (100 . "AcDbPolyline") (90 . 2) (70 . 0)
(43 . 0.0) (10 16167.0418552036 246.9824660633) (10 16138.7613122172 248.8687782805))
((0 . "LWPOLYLINE") (100 . "AcDbEntity") (8 . "PLANTS") (62 . 94) (370 . 13) (100 . "AcDbPolyline") (90 . 3) (70 . 0)
(43 . 0.0) (10 16146.306561086 6874.0575791855) (10 16153.8530542986 6867.7070135747) (10 16187.7828054299
6858.9740950226))
((0 . "LWPOLYLINE") (100 . "AcDbEntity") (8 . "PLANTS") (62 . 94) (370 . 13) (100 . "AcDbPolyline") (90 . 3) (70 . 0)
(43 . 0.0) (10 16146.306561086 6874.0575791855) (10 16156.5609728507 6896.6820135747) (10 16161.3857466063
6923.0769230769))
((0 . "LWPOLYLINE") (100 . "AcDbEntity") (8 . "PLANTS") (62 . 94) (370 . 13) (100 . "AcDbPolyline") (90 . 2) (70 . 0)
(43 . 0.0) (10 16146.306561086 456.2584841629) (10 16153.8461538462 456.2584841629))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2292858361)
(40 . 0.3321456622) (40 . 1) (40 . 1) (40 . 1) (40 . 1) (10 16146.306561086 392.1578054297 0.0) (10 16159.9991933318
389.0819936356 0.0) (10 16183.8367227649 393.0932112597 0.0) (10 16247.327343916 375.4674026377 0.0) (10
16265.4354305036 305.5353513169 0.0) (10 16308.4445701357 294.1176470588 0.0))
((0 . "LWPOLYLINE") (100 . "AcDbEntity") (8 . "PLANTS") (62 . 94) (370 . 13) (100 . "AcDbPolyline") (90 . 3) (70 . 0)
(43 . 0.0) (10 16146.306561086 392.1578054299) (10 16157.4695701357 418.5520361991) (10 16153.8461538462
456.2584841629))
((0 . "LWPOLYLINE") (100 . "AcDbEntity") (8 . "PLANTS") (62 . 94) (370 . 13) (100 . "AcDbPolyline") (90 . 3) (70 . 0)
(43 . 0.0) (10 16226.8250587956 6485.6899433634) (10 16157.6228506787 6485.8194570136) (10 16150.0735294118
6489.4418552036))
((0 . "LWPOLYLINE") (100 . "AcDbEntity") (8 . "PLANTS") (62 . 94) (370 . 13) (100 . "AcDbPolyline") (90 . 3) (70 . 0)
(43 . 0.0) (10 16150.0735294118 6489.4418552036) (10 16161.0916289593 6530.9197963801) (10 16157.6187782805
6542.2320135747))
((0 . "LWPOLYLINE") (100 . "AcDbEntity") (8 . "PLANTS") (62 . 94) (370 . 13) (100 . "AcDbPolyline") (90 . 3) (70 . 0)
(43 . 0.0) (10 16150.0735294118 320.5118778281) (10 16176.4636877828 331.9725113122) (10 16184.0101809955
346.9089366516))
((0 . "LWPOLYLINE") (100 . "AcDbEntity") (8 . "PLANTS") (62 . 94) (370 . 13) (100 . "AcDbPolyline") (90 . 2) (70 . 0)
(43 . 0.0) (10 16153.8461538462 6953.2430995475) (10 16153.8461538462 6938.1596153846))
((0 . "LWPOLYLINE") (100 . "AcDbEntity") (8 . "PLANTS") (62 . 94) (370 . 13) (100 . "AcDbPolyline") (90 . 3) (70 . 0)
(43 . 0.0) (10 16161.3857466063 6923.0769230769) (10 16160.1899321267 6934.2342760181) (10 16153.8461538462
6938.1596153846))
((0 . "LWPOLYLINE") (100 . "AcDbEntity") (8 . "PLANTS") (62 . 94) (370 . 13) (100 . "AcDbPolyline") (90 . 2) (70 . 0)
(43 . 0.0) (10 16206.6346153846 6783.559841629) (10 16153.8461538462 6783.559841629))
((0 . "LWPOLYLINE") (100 . "AcDbEntity") (8 . "PLANTS") (62 . 94) (370 . 13) (100 . "AcDbPolyline") (90 . 3) (70 . 0)
(43 . 0.0) (10 16187.7828054299 6832.5791855204) (10 16162.4435520362 6809.9547511312) (10 16153.8461538462
6783.559841629))
((0 . "LWPOLYLINE") (100 . "AcDbEntity") (8 . "PLANTS") (62 . 94) (370 . 13) (100 . "AcDbPolyline") (90 . 3) (70 . 0)
(43 . 0.0) (10 16161.3857466063 467.5707013575) (10 16153.8461538462 463.8009049774) (10 16153.8461538462
456.2584841629))
((0 . "LWPOLYLINE") (100 . "AcDbEntity") (8 . "PLANTS") (62 . 94) (370 . 13) (100 . "AcDbPolyline") (90 . 3) (70 . 0)
(43 . 0.0) (10 16210.407239819 6911.7647058824) (10 16191.5554298643 6919.1581447964) (10 16161.3857466063
6923.0769230769))
((0 . "LWPOLYLINE") (100 . "AcDbEntity") (8 . "PLANTS") (62 . 94) (370 . 13) (100 . "AcDbPolyline") (90 . 3) (70 . 0)
(43 . 0.0) (10 16167.0418552036 246.9824660633) (10 16195.32239819 244.0418552036) (10 16206.6346153846 233.7867647059))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16167.0418552036 246.9824660633 0.0) (10 16168.4485704105 228.4377518766 0.0) (10 16195.7046673323
210.6216601541 0.0) (10 16206.6346153846 233.7867647059 0.0))
((0 . "LWPOLYLINE") (100 . "AcDbEntity") (8 . "PLANTS") (62 . 94) (370 . 13) (100 . "AcDbPolyline") (90 . 3) (70 . 0)
(43 . 0.0) (10 16167.0418552036 246.9824660633) (10 16169.1559954751 256.3428733032) (10 16187.7828054299
279.0356334842))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16195.3223981901 7009.8041855204 0.0) (10 16181.1149489424 7008.7472969998 0.0) (10 16173.0119025223
7025.5306718436 0.0) (10 16168.9309954751 7036.1990950226 0.0))
((0 . "LWPOLYLINE") (100 . "AcDbEntity") (8 . "PLANTS") (62 . 94) (370 . 13) (100 . "AcDbPolyline") (90 . 2) (70 . 0)
(43 . 0.0) (10 16172.6979638009 6406.4857466063) (10 16168.9309954751 6414.0271493213))
((0 . "LWPOLYLINE") (100 . "AcDbEntity") (8 . "PLANTS") (62 . 94) (370 . 13) (100 . "AcDbPolyline") (90 . 2) (70 . 0)
(43 . 0.0) (10 16212.9659716631 7114.6169958314) (10 16176.4705882353 7062.5940045249))
((0 . "LWPOLYLINE") (100 . "AcDbEntity") (8 . "PLANTS") (62 . 94) (370 . 13) (100 . "AcDbPolyline") (90 . 2) (70 . 0)
(43 . 0.0) (10 16184.0101809955 346.9089366516) (10 16180.2432126697 358.2211538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16289.592760181 252.6385746606 0.0) (10 16260.213574217 272.7081584014 0.0) (10 16235.5129104092
347.7002473254 0.0) (10 16184.0101809955 346.9089366516 0.0))
((0 . "LWPOLYLINE") (100 . "AcDbEntity") (8 . "PLANTS") (62 . 94) (370 . 13) (100 . "AcDbPolyline") (90 . 2) (70 . 0)
(43 . 0.0) (10 16187.7828054299 6858.9740950226) (10 16187.7828054299 6832.5791855204))
((0 . "LWPOLYLINE") (100 . "AcDbEntity") (8 . "PLANTS") (62 . 94) (370 . 13) (100 . "AcDbPolyline") (90 . 2) (70 . 0)
(43 . 0.0) (10 16206.6346153846 6862.745361991) (10 16187.7828054299 6858.9740950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16206.6346153846 6783.559841629 0.0) (10 16183.6810436425 6792.5908196051 0.0) (10 16209.1087392124
6826.3813332238 0.0) (10 16187.7828054299 6832.5791855204 0.0))
((0 . "LWPOLYLINE") (100 . "AcDbEntity") (8 . "PLANTS") (62 . 94) (370 . 13) (100 . "AcDbPolyline") (90 . 3) (70 . 0)
(43 . 0.0) (10 16195.32239819 7009.8041855204) (10 16195.32239819 6998.4919683258) (10 16199.0950226244
6994.7207013575))
((0 . "LWPOLYLINE") (100 . "AcDbEntity") (8 . "PLANTS") (62 . 94) (370 . 13) (100 . "AcDbPolyline") (90 . 2) (70 . 0)
(43 . 0.0) (10 16195.32239819 7009.8041855204) (10 16233.0316742081 7028.6573529412))
((0 . "LWPOLYLINE") (100 . "AcDbEntity") (8 . "PLANTS") (62 . 94) (370 . 13) (100 . "AcDbPolyline") (90 . 2) (70 . 0)
(43 . 0.0) (10 16210.407239819 6711.9152714932) (10 16202.8676470588 6711.9152714932))
((0 . "LWPOLYLINE") (100 . "AcDbEntity") (8 . "PLANTS") (62 . 94) (370 . 13) (100 . "AcDbPolyline") (90 . 2) (70 . 0)
(43 . 0.0) (10 16206.6346153846 6862.745361991) (10 16240.5712669683 6862.745361991))
((0 . "LWPOLYLINE") (100 . "AcDbEntity") (8 . "PLANTS") (62 . 94) (370 . 13) (100 . "AcDbPolyline") (90 . 3) (70 . 0)
(43 . 0.0) (10 16206.6346153846 6862.745361991) (10 16210.2595022624 6874.0575791855) (10 16210.407239819
6911.7647058824))
((0 . "LWPOLYLINE") (100 . "AcDbEntity") (8 . "PLANTS") (62 . 94) (370 . 13) (100 . "AcDbPolyline") (90 . 2) (70 . 0)
(43 . 0.0) (10 16214.1798642534 6764.7058823529) (10 16206.6346153846 6783.559841629))
((0 . "LWPOLYLINE") (100 . "AcDbEntity") (8 . "PLANTS") (62 . 94) (370 . 13) (100 . "AcDbPolyline") (90 . 2) (70 . 0)
(43 . 0.0) (10 16206.6346153846 471.3433257919) (10 16229.2590497738 467.5707013575))
((0 . "LWPOLYLINE") (100 . "AcDbEntity") (8 . "PLANTS") (62 . 94) (370 . 13) (100 . "AcDbPolyline") (90 . 2) (70 . 0)
(43 . 0.0) (10 16206.6346153846 233.7867647059) (10 16233.0316742081 237.556561086))
((0 . "LWPOLYLINE") (100 . "AcDbEntity") (8 . "PLANTS") (62 . 94) (370 . 13) (100 . "AcDbPolyline") (90 . 2) (70 . 0)
(43 . 0.0) (10 16236.8042986425 6924.9625565611) (10 16210.407239819 6911.7647058824))
((0 . "LWPOLYLINE") (100 . "AcDbEntity") (8 . "PLANTS") (62 . 94) (370 . 13) (100 . "AcDbPolyline") (90 . 3) (70 . 0)
(43 . 0.0) (10 16210.407239819 6711.9152714932) (10 16248.1165158371 6694.1180995475) (10 16250.1619876582
6693.927154753))
((0 . "LWPOLYLINE") (100 . "AcDbEntity") (8 . "PLANTS") (62 . 94) (370 . 13) (100 . "AcDbPolyline") (90 . 2) (70 . 0)
(43 . 0.0) (10 16210.407239819 6711.9152714932) (10 16214.1798642534 6764.7058823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16214.1798642534 6764.7058823529 0.0) (10 16243.8272844142 6778.8785813254 0.0) (10 16270.7559087494
6751.5386051161 0.0) (10 16300.9049773756 6760.9354072398 0.0))
((0 . "LWPOLYLINE") (100 . "AcDbEntity") (8 . "PLANTS") (62 . 94) (370 . 13) (100 . "AcDbPolyline") (90 . 2) (70 . 0)
(43 . 0.0) (10 16225.492081448 6613.8765837104) (10 16214.1798642534 6591.2521493213))
((0 . "LWPOLYLINE") (100 . "AcDbEntity") (8 . "PLANTS") (62 . 94) (370 . 13) (100 . "AcDbPolyline") (90 . 2) (70 . 0)
(43 . 0.0) (10 16240.8299277634 6610.6564664613) (10 16225.492081448 6613.8765837104))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16245.8272036559 6655.2475436554 0.0) (10 16223.9493955866 6658.8541339404 0.0) (10 16214.0352894349
6630.1745837021 0.0) (10 16225.492081448 6613.8765837104 0.0))
((0 . "LWPOLYLINE") (100 . "AcDbEntity") (8 . "PLANTS") (62 . 94) (370 . 13) (100 . "AcDbPolyline") (90 . 2) (70 . 0)
(43 . 0.0) (10 16233.0316742081 237.556561086) (10 16225.492081448 256.411199095))
((0 . "LWPOLYLINE") (100 . "AcDbEntity") (8 . "PLANTS") (62 . 94) (370 . 13) (100 . "AcDbPolyline") (90 . 2) (70 . 0)
(43 . 0.0) (10 16233.0316742081 7028.6573529412) (10 16248.1165158371 7021.1164027149))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3629772006) (40
. 1) (40 . 1) (40 . 1) (40 . 1) (10 16274.5079185521 7039.9695701357 0.0) (10 16288.60767095 7049.8237980477 0.0) (10
16263.5228394817 7117.2495956967 0.0) (10 16210.2078348997 7062.7870219895 0.0) (10 16233.0316742082 7028.6573529412
0.0))
((0 . "LWPOLYLINE") (100 . "AcDbEntity") (8 . "PLANTS") (62 . 94) (370 . 13) (100 . "AcDbPolyline") (90 . 2) (70 . 0)
(43 . 0.0) (10 16259.4287330317 6968.3257918552) (10 16233.0316742081 6968.3257918552))
((0 . "LWPOLYLINE") (100 . "AcDbEntity") (8 . "PLANTS") (62 . 94) (370 . 13) (100 . "AcDbPolyline") (90 . 3) (70 . 0)
(43 . 0.0) (10 16236.8042986425 6924.9625565611) (10 16229.415158371 6938.1566742081) (10 16233.0316742081
6968.3257918552))
((0 . "LWPOLYLINE") (100 . "AcDbEntity") (8 . "PLANTS") (62 . 94) (370 . 13) (100 . "AcDbPolyline") (90 . 2) (70 . 0)
(43 . 0.0) (10 16236.8042986425 6990.9502262443) (10 16233.0316742081 6968.3257918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16353.693438914 429.8642533937 0.0) (10 16332.0813888652 470.1475089886 0.0) (10 16270.3615933865
462.9829474959 0.0) (10 16260.4764496799 515.5887277101 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16440.4242081449 411.0096153846 0.0) (10 16438.3436635272 472.1519990907 0.0) (10 16390.7358266076
528.0857549944 0.0) (10 16339.2928739774 557.3293259532 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16304.8841535047 531.9494606982 0.0) (10 16340.6894648926 508.1994021128 0.0) (10 16380.7208954469
479.1688019861 0.0) (10 16387.6300904977 433.6340497738 0.0))
((0 . "LWPOLYLINE") (100 . "AcDbEntity") (8 . "PLANTS") (62 . 94) (370 . 13) (100 . "AcDbPolyline") (90 . 3) (70 . 0)
(43 . 0.0) (10 16289.592760181 252.6385746606) (10 16270.7409502262 237.711199095) (10 16233.0316742081 237.556561086))
((0 . "LWPOLYLINE") (100 . "AcDbEntity") (8 . "PLANTS") (62 . 94) (370 . 13) (100 . "AcDbPolyline") (90 . 3) (70 . 0)
(43 . 0.0) (10 16236.8042986425 6924.9625565611) (10 16248.1165158371 6912.9721719457) (10 16263.1957013575
6907.9942307692))
((0 . "LWPOLYLINE") (100 . "AcDbEntity") (8 . "PLANTS") (62 . 94) (370 . 13) (100 . "AcDbPolyline") (90 . 2) (70 . 0)
(43 . 0.0) (10 16236.8042986425 6924.9625565611) (10 16263.1957013575 6953.2430995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16300.9049773756 6772.2476244344 0.0) (10 16305.287139772 6823.2531197693 0.0) (10 16232.6813736458
6812.7976318704 0.0) (10 16240.5712669683 6862.745361991 0.0))
((0 . "LWPOLYLINE") (100 . "AcDbEntity") (8 . "PLANTS") (62 . 94) (370 . 13) (100 . "AcDbPolyline") (90 . 2) (70 . 0)
(43 . 0.0) (10 16240.5712669683 6862.745361991) (10 16259.4287330317 6866.5158371041))
((0 . "LWPOLYLINE") (100 . "AcDbEntity") (8 . "PLANTS") (62 . 94) (370 . 13) (100 . "AcDbPolyline") (90 . 3) (70 . 0)
(43 . 0.0) (10 16259.4287330317 6968.3257918552) (10 16259.4287330317 6957.0135746606) (10 16263.1957013575
6953.2430995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16319.7567873303 7013.5746606335 0.0) (10 16293.1418659963 7010.8275952654 0.0) (10 16270.8890698808
6991.571572244 0.0) (10 16259.4287330317 6968.3257918552 0.0))
((0 . "LWPOLYLINE") (100 . "AcDbEntity") (8 . "PLANTS") (62 . 94) (370 . 13) (100 . "AcDbPolyline") (90 . 3) (70 . 0)
(43 . 0.0) (10 16259.4287330317 6866.5158371041) (10 16315.9814479638 6830.0062217195) (10 16323.5294117647
6828.8087104072))
((0 . "LWPOLYLINE") (100 . "AcDbEntity") (8 . "PLANTS") (62 . 94) (370 . 13) (100 . "AcDbPolyline") (90 . 2) (70 . 0)
(43 . 0.0) (10 16263.1957013575 6907.9942307692) (10 16259.4287330317 6866.5158371041))
((0 . "LWPOLYLINE") (100 . "AcDbEntity") (8 . "PLANTS") (62 . 94) (370 . 13) (100 . "AcDbPolyline") (90 . 2) (70 . 0)
(43 . 0.0) (10 16274.507918552 6957.0135746606) (10 16263.1957013575 6953.2430995475))
((0 . "LWPOLYLINE") (100 . "AcDbEntity") (8 . "PLANTS") (62 . 94) (370 . 13) (100 . "AcDbPolyline") (90 . 2) (70 . 0)
(43 . 0.0) (10 16263.1957013575 6907.9942307692) (10 16331.0690045249 6911.7647058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16304.67760181 343.1363122172 0.0) (10 16279.6322044906 342.9820197279 0.0) (10 16285.1060474907
385.154677329 0.0) (10 16282.0531674208 395.92760181 0.0))
((0 . "LWPOLYLINE") (100 . "AcDbEntity") (8 . "PLANTS") (62 . 94) (370 . 13) (100 . "AcDbPolyline") (90 . 2) (70 . 0)
(43 . 0.0) (10 16289.592760181 252.6385746606) (10 16315.9898190045 252.6385746606))
((0 . "LWPOLYLINE") (100 . "AcDbEntity") (8 . "PLANTS") (62 . 94) (370 . 13) (100 . "AcDbPolyline") (90 . 2) (70 . 0)
(43 . 0.0) (10 16300.9049773756 6772.2476244344) (10 16300.9049773756 6760.9354072398))
((0 . "LWPOLYLINE") (100 . "AcDbEntity") (8 . "PLANTS") (62 . 94) (370 . 13) (100 . "AcDbPolyline") (90 . 2) (70 . 0)
(43 . 0.0) (10 16300.9049773756 6772.2476244344) (10 16334.8416289593 6779.7885746606))
((0 . "LWPOLYLINE") (100 . "AcDbEntity") (8 . "PLANTS") (62 . 94) (370 . 13) (100 . "AcDbPolyline") (90 . 3) (70 . 0)
(43 . 0.0) (10 16300.9049773756 6760.9354072398) (10 16304.8308823529 6749.6297511312) (10 16315.9898190045
6738.3107466063))
((0 . "LWPOLYLINE") (100 . "AcDbEntity") (8 . "PLANTS") (62 . 94) (370 . 13) (100 . "AcDbPolyline") (90 . 3) (70 . 0)
(43 . 0.0) (10 16304.67760181 343.1363122172) (10 16308.2981900452 331.8240950226) (10 16308.4445701357 294.1176470588))
((0 . "LWPOLYLINE") (100 . "AcDbEntity") (8 . "PLANTS") (62 . 94) (370 . 13) (100 . "AcDbPolyline") (90 . 3) (70 . 0)
(43 . 0.0) (10 16304.67760181 343.1363122172) (10 16312.0763574661 347.0622171946) (10 16334.8416289593 380.8455882353))
((0 . "LWPOLYLINE") (100 . "AcDbEntity") (8 . "PLANTS") (62 . 94) (370 . 13) (100 . "AcDbPolyline") (90 . 3) (70 . 0)
(43 . 0.0) (10 16308.4445701357 294.1176470588) (10 16312.2171945701 286.5752262443) (10 16315.9898190045
286.5752262443))
((0 . "LWPOLYLINE") (100 . "AcDbEntity") (8 . "PLANTS") (62 . 94) (370 . 13) (100 . "AcDbPolyline") (90 . 2) (70 . 0)
(43 . 0.0) (10 16315.9898190045 271.4932126697) (10 16315.9898190045 286.5752262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16315.9898190045 286.5752262443 0.0) (10 16346.7506191852 295.1881832844 0.0) (10 16341.1700086068
336.6867233836 0.0) (10 16372.5509049774 343.1363122172 0.0))
((0 . "LWPOLYLINE") (100 . "AcDbEntity") (8 . "PLANTS") (62 . 94) (370 . 13) (100 . "AcDbPolyline") (90 . 2) (70 . 0)
(43 . 0.0) (10 16315.9898190045 271.4932126697) (10 16315.9898190045 252.6385746606))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16383.863122172 312.9722850679 0.0) (10 16369.3528573432 291.5164197765 0.0) (10 16344.0908148454
269.1869636177 0.0) (10 16315.9898190045 271.4932126697 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16436.6515837104 237.556561086 0.0) (10 16397.4488169135 227.6970651843 0.0) (10 16340.2394505608
214.3216643026 0.0) (10 16315.9898190045 252.6385746606 0.0))
((0 . "LWPOLYLINE") (100 . "AcDbEntity") (8 . "PLANTS") (62 . 94) (370 . 13) (100 . "AcDbPolyline") (90 . 2) (70 . 0)
(43 . 0.0) (10 16327.3020361991 6990.9502262443) (10 16319.7567873303 7013.5746606335))
((0 . "LWPOLYLINE") (100 . "AcDbEntity") (8 . "PLANTS") (62 . 94) (370 . 13) (100 . "AcDbPolyline") (90 . 2) (70 . 0)
(43 . 0.0) (10 16323.5294117647 7039.9695701357) (10 16319.7567873303 7013.5746606335))
((0 . "LWPOLYLINE") (100 . "AcDbEntity") (8 . "PLANTS") (62 . 94) (370 . 13) (100 . "AcDbPolyline") (90 . 2) (70 . 0)
(43 . 0.0) (10 16323.5294117647 7081.4479638009) (10 16323.5294117647 7039.9695701357))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16323.5294117647 7039.9695701357 0.0) (10 16353.1333563679 7035.5853986122 0.0) (10 16374.1534861844
7070.2310977227 0.0) (10 16391.4027149321 7085.218438914 0.0))
((0 . "LWPOLYLINE") (100 . "AcDbEntity") (8 . "PLANTS") (62 . 94) (370 . 13) (100 . "AcDbPolyline") (90 . 3) (70 . 0)
(43 . 0.0) (10 16334.8416289593 6779.7885746606) (10 16327.4484162896 6798.6425339367) (10 16323.5294117647
6828.8087104072))
((0 . "LWPOLYLINE") (100 . "AcDbEntity") (8 . "PLANTS") (62 . 94) (370 . 13) (100 . "AcDbPolyline") (90 . 2) (70 . 0)
(43 . 0.0) (10 16323.5294117647 6828.8087104072) (10 16380.0904977376 6847.6618778281))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16334.8416289593 6923.0769230769 0.0) (10 16307.4282031007 6930.6235508977 0.0) (10 16319.8035744727
6979.0704896096 0.0) (10 16327.3020361991 6990.9502262443 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16327.3020361991 6990.9502262443 0.0) (10 16360.0216470055 6986.5058413297 0.0) (10 16376.6218867751
7020.6653465663 0.0) (10 16406.4875565611 7024.8868778281 0.0))
((0 . "LWPOLYLINE") (100 . "AcDbEntity") (8 . "PLANTS") (62 . 94) (370 . 13) (100 . "AcDbPolyline") (90 . 3) (70 . 0)
(43 . 0.0) (10 16346.1538461538 6900.4524886878) (10 16338.7522624434 6901.6567873303) (10 16331.0690045249
6911.7647058824))
((0 . "LWPOLYLINE") (100 . "AcDbEntity") (8 . "PLANTS") (62 . 94) (370 . 13) (100 . "AcDbPolyline") (90 . 2) (70 . 0)
(43 . 0.0) (10 16334.8416289593 6923.0769230769) (10 16331.0690045249 6911.7647058824))
((0 . "LWPOLYLINE") (100 . "AcDbEntity") (8 . "PLANTS") (62 . 94) (370 . 13) (100 . "AcDbPolyline") (90 . 3) (70 . 0)
(43 . 0.0) (10 16334.8416289593 6923.0769230769) (10 16368.778280543 6956.6450226244) (10 16380.0904977376
6957.0135746606))
((0 . "LWPOLYLINE") (100 . "AcDbEntity") (8 . "PLANTS") (62 . 94) (370 . 13) (100 . "AcDbPolyline") (90 . 3) (70 . 0)
(43 . 0.0) (10 16334.8416289593 6779.7885746606) (10 16383.8631221719 6783.553280543) (10 16708.1447963801
6783.559841629))
((0 . "LWPOLYLINE") (100 . "AcDbEntity") (8 . "PLANTS") (62 . 94) (370 . 13) (100 . "AcDbPolyline") (90 . 2) (70 . 0)
(43 . 0.0) (10 16353.693438914 429.8642533937) (10 16342.3812217195 407.2398190045))
((0 . "LWPOLYLINE") (100 . "AcDbEntity") (8 . "PLANTS") (62 . 94) (370 . 13) (100 . "AcDbPolyline") (90 . 3) (70 . 0)
(43 . 0.0) (10 16346.1538461538 6900.4524886878) (10 16368.6305429864 6877.8280542986) (10 16380.0904977376
6858.9740950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16455.5033936652 6930.6186651584 0.0) (10 16418.2092440595 6932.1599931681 0.0) (10 16372.6871727183
6931.454622277 0.0) (10 16346.1538461538 6900.4524886878 0.0))
((0 . "LWPOLYLINE") (100 . "AcDbEntity") (8 . "PLANTS") (62 . 94) (370 . 13) (100 . "AcDbPolyline") (90 . 2) (70 . 0)
(43 . 0.0) (10 16357.9690401653 617.5080836699) (10 16383.8631221719 614.6295248869))
((0 . "LWPOLYLINE") (100 . "AcDbEntity") (8 . "PLANTS") (62 . 94) (370 . 13) (100 . "AcDbPolyline") (90 . 2) (70 . 0)
(43 . 0.0) (10 16353.693438914 429.8642533937) (10 16372.5509049774 429.8642533937))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16372.5509049774 429.8642533937 0.0) (10 16368.5146129736 388.2078068383 0.0) (10 16413.1007704139
353.6633695101 0.0) (10 16449.8472850679 346.9089366516 0.0))
((0 . "LWPOLYLINE") (100 . "AcDbEntity") (8 . "PLANTS") (62 . 94) (370 . 13) (100 . "AcDbPolyline") (90 . 3) (70 . 0)
(43 . 0.0) (10 16372.5509049774 429.8642533937) (10 16376.3178733032 433.6340497738) (10 16387.6300904977
433.6340497738))
((0 . "LWPOLYLINE") (100 . "AcDbEntity") (8 . "PLANTS") (62 . 94) (370 . 13) (100 . "AcDbPolyline") (90 . 2) (70 . 0)
(43 . 0.0) (10 16372.5509049774 350.6787330317) (10 16372.5509049774 343.1363122172))
((0 . "LWPOLYLINE") (100 . "AcDbEntity") (8 . "PLANTS") (62 . 94) (370 . 13) (100 . "AcDbPolyline") (90 . 3) (70 . 0)
(43 . 0.0) (10 16383.8631221719 312.9722850679) (10 16382.6631221719 328.0542986425) (10 16372.5509049774
343.1363122172))
((0 . "LWPOLYLINE") (100 . "AcDbEntity") (8 . "PLANTS") (62 . 94) (370 . 13) (100 . "AcDbPolyline") (90 . 2) (70 . 0)
(43 . 0.0) (10 16380.0904977376 6847.6618778281) (10 16380.0904977376 6858.9740950226))
((0 . "LWPOLYLINE") (100 . "AcDbEntity") (8 . "PLANTS") (62 . 94) (370 . 13) (100 . "AcDbPolyline") (90 . 3) (70 . 0)
(43 . 0.0) (10 16440.4242081448 6881.5985294118) (10 16406.4875565611 6876.7720588235) (10 16380.0904977376
6858.9740950226))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16455.5033936652 6847.661877828 0.0) (10 16441.3271807462 6821.5349809197 0.0) (10 16398.099929666
6831.1309036985 0.0) (10 16380.0904977376 6847.661877828 0.0))
((0 . "LWPOLYLINE") (100 . "AcDbEntity") (8 . "PLANTS") (62 . 94) (370 . 13) (100 . "AcDbPolyline") (90 . 2) (70 . 0)
(43 . 0.0) (10 16383.8631221719 312.9722850679) (10 16406.4875565611 301.6600678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16387.6300904977 6738.3107466063 0.0) (10 16478.1278280543 6738.3107466063 0.0) (10 16568.6255656109
6738.3107466063 0.0) (10 16659.1233031674 6738.3107466063 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4371588949) (40
. 1) (40 . 1) (40 . 1) (40 . 1) (10 16538.4615384616 554.298642534 0.0) (10 16534.0024565051 595.6743396848 0.0) (10
16495.0829147755 682.9093090575 0.0) (10 16459.5672477708 771.4666576244 0.0) (10 16416.8514041392 807.2401453634 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3527272781) (40
. 1) (40 . 1) (40 . 1) (40 . 1) (10 16400.8421106128 755.6546440003 0.0) (10 16400.1321460445 734.6426136691 0.0) (10
16424.8509211976 683.6080829732 0.0) (10 16431.0340054182 620.9710290349 0.0) (10 16459.2760180995 595.777714932 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16440.4242081448 411.0096153846 0.0) (10 16412.8691742247 398.7175972968 0.0) (10 16409.0201518888
434.9511631659 0.0) (10 16387.6300904977 433.6340497738 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4000740147)
(40 . 0.7717192043) (40 . 1) (40 . 1) (40 . 1) (40 . 1) (10 16406.4875565611 7024.8868778281 0.0) (10 16429.0889159295
7016.1579093616 0.0) (10 16402.2702688943 6970.4659110859 0.0) (10 16460.394412394 6969.5013482105 0.0) (10
16477.1706175543 6950.5728346982 0.0) (10 16474.3608597285 6938.1596153846 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16406.4875565611 7024.8868778281 0.0) (10 16403.3249203171 7049.0448818781 0.0) (10 16434.660746789
7064.5400719253 0.0) (10 16451.7364253394 7070.1357466063 0.0))
((0 . "LWPOLYLINE") (100 . "AcDbEntity") (8 . "PLANTS") (62 . 94) (370 . 13) (100 . "AcDbPolyline") (90 . 3) (70 . 0)
(43 . 0.0) (10 16436.6515837104 237.556561086) (10 16431.6831447964 260.0263574661) (10 16414.0271493213
267.7234162896))
((0 . "LWPOLYLINE") (100 . "AcDbEntity") (8 . "PLANTS") (62 . 94) (370 . 13) (100 . "AcDbPolyline") (90 . 3) (70 . 0)
(43 . 0.0) (10 16436.6515837104 237.556561086) (10 16474.3608597285 233.9400452489) (10 16485.6730769231
241.3263574661))
((0 . "LWPOLYLINE") (100 . "AcDbEntity") (8 . "PLANTS") (62 . 94) (370 . 13) (100 . "AcDbPolyline") (90 . 2) (70 . 0)
(43 . 0.0) (10 16455.5033936652 6847.6618778281) (10 16440.4242081448 6881.5985294118))
((0 . "LWPOLYLINE") (100 . "AcDbEntity") (8 . "PLANTS") (62 . 94) (370 . 13) (100 . "AcDbPolyline") (90 . 3) (70 . 0)
(43 . 0.0) (10 16455.5033936652 6900.4524886878) (10 16445.2489819005 6892.7632352941) (10 16440.4242081448
6881.5985294118))
((0 . "LWPOLYLINE") (100 . "AcDbEntity") (8 . "PLANTS") (62 . 94) (370 . 13) (100 . "AcDbPolyline") (90 . 2) (70 . 0)
(43 . 0.0) (10 16444.1911764706 399.69739819) (10 16440.4242081448 411.0096153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16444.1911764706 399.69739819 0.0) (10 16460.1079763347 404.1030376725 0.0) (10 16479.6716667381
396.8195355803 0.0) (10 16485.6730769231 380.8455882353 0.0))
((0 . "LWPOLYLINE") (100 . "AcDbEntity") (8 . "PLANTS") (62 . 94) (370 . 13) (100 . "AcDbPolyline") (90 . 3) (70 . 0)
(43 . 0.0) (10 16444.1911764706 399.69739819) (10 16451.5872171946 361.9909502262) (10 16449.8472850679 346.9089366516))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16449.8472850678 346.9089366516 0.0) (10 16504.7451397312 350.309600729 0.0) (10 16490.0083830335
273.9698533728 0.0) (10 16530.9219457013 252.6385746606 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16485.6730769231 241.3263574661 0.0) (10 16482.0434758963 279.8493356072 0.0) (10 16435.7142792459
304.8712933138 0.0) (10 16449.8472850679 346.9089366516 0.0))
((0 . "LWPOLYLINE") (100 . "AcDbEntity") (8 . "PLANTS") (62 . 94) (370 . 13) (100 . "AcDbPolyline") (90 . 2) (70 . 0)
(43 . 0.0) (10 16455.5033936652 6930.6186651584) (10 16455.5033936652 6900.4524886878))
((0 . "LWPOLYLINE") (100 . "AcDbEntity") (8 . "PLANTS") (62 . 94) (370 . 13) (100 . "AcDbPolyline") (90 . 2) (70 . 0)
(43 . 0.0) (10 16455.5033936652 6930.6186651584) (10 16474.3608597285 6938.1596153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16478.1278280543 6847.661877828 0.0) (10 16510.8294274427 6867.9026754831 0.0) (10 16483.926588878
6902.8273290718 0.0) (10 16455.5033936652 6900.4524886878 0.0))
((0 . "LWPOLYLINE") (100 . "AcDbEntity") (8 . "PLANTS") (62 . 94) (370 . 13) (100 . "AcDbPolyline") (90 . 2) (70 . 0)
(43 . 0.0) (10 16478.1278280543 6847.6618778281) (10 16455.5033936652 6847.6618778281))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16459.2760180995 595.7777149321 0.0) (10 16455.2662528431 550.3914435242 0.0) (10 16468.0340517878
493.5872735068 0.0) (10 16508.2975113122 467.5707013575 0.0))
((0 . "LWPOLYLINE") (100 . "AcDbEntity") (8 . "PLANTS") (62 . 94) (370 . 13) (100 . "AcDbPolyline") (90 . 2) (70 . 0)
(43 . 0.0) (10 16489.4400452489 618.4021493213) (10 16459.2760180996 595.7777149321))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16546.0011312217 6900.4524886878 0.0) (10 16517.611336404 6905.4066524618 0.0) (10 16503.2078662643
6934.7145712361 0.0) (10 16474.3608597285 6938.1596153846 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16478.1278280543 6847.6618778281 0.0) (10 16492.679571258 6833.6451075446 0.0) (10 16517.8225137095
6833.8979983448 0.0) (10 16534.6889140272 6843.8914027149 0.0))
((0 . "LWPOLYLINE") (100 . "AcDbEntity") (8 . "PLANTS") (62 . 94) (370 . 13) (100 . "AcDbPolyline") (90 . 3) (70 . 0)
(43 . 0.0) (10 16485.6730769231 241.3263574661) (10 16515.8371040724 241.4816742081) (10 16530.9219457014
252.6385746606))
((0 . "LWPOLYLINE") (100 . "AcDbEntity") (8 . "PLANTS") (62 . 94) (370 . 13) (100 . "AcDbPolyline") (90 . 2) (70 . 0)
(43 . 0.0) (10 16496.9852941176 550.5288461538) (10 16496.9852941176 561.8410633484))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16553.5463800905 312.9722850678 0.0) (10 16494.1915394681 337.5084767314 0.0) (10 16558.11030759
433.5367170691 0.0) (10 16508.2975113122 467.5707013575 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16538.4615384615 554.2986425339 0.0) (10 16509.283478936 534.380711127 0.0) (10 16536.6694866575
488.8742536759 0.0) (10 16508.2975113122 467.5707013575 0.0))
((0 . "LWPOLYLINE") (100 . "AcDbEntity") (8 . "PLANTS") (62 . 94) (370 . 13) (100 . "AcDbPolyline") (90 . 3) (70 . 0)
(43 . 0.0) (10 16564.8585972851 6972.0962669683) (10 16538.468438914 6978.4271493213) (10 16527.149321267
6960.7840497738))
((0 . "LWPOLYLINE") (100 . "AcDbEntity") (8 . "PLANTS") (62 . 94) (370 . 13) (100 . "AcDbPolyline") (90 . 3) (70 . 0)
(43 . 0.0) (10 16564.8585972851 267.7234162896) (10 16553.3958144796 253.843438914) (10 16530.9219457014
252.6385746606))
((0 . "LWPOLYLINE") (100 . "AcDbEntity") (8 . "PLANTS") (62 . 94) (370 . 13) (100 . "AcDbPolyline") (90 . 2) (70 . 0)
(43 . 0.0) (10 16561.0859728507 6840.1209276018) (10 16534.6889140272 6843.8914027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16551.657239819 6887.254638009 0.0) (10 16534.6741241298 6881.7762720017 0.0) (10 16530.7865766789
6858.6780469952 0.0) (10 16534.6889140272 6843.8914027149 0.0))
((0 . "LWPOLYLINE") (100 . "AcDbEntity") (8 . "PLANTS") (62 . 94) (370 . 13) (100 . "AcDbPolyline") (90 . 2) (70 . 0)
(43 . 0.0) (10 16564.8585972851 554.2986425339) (10 16538.4615384615 554.2986425339))
((0 . "LWPOLYLINE") (100 . "AcDbEntity") (8 . "PLANTS") (62 . 94) (370 . 13) (100 . "AcDbPolyline") (90 . 3) (70 . 0)
(43 . 0.0) (10 16551.657239819 6887.254638009) (10 16546.0011312217 6892.9107466063) (10 16546.0011312217
6900.4524886878))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16546.0011312217 6900.4524886878 0.0) (10 16563.9137975593 6906.2646655772 0.0) (10 16550.6702226221
6926.6653477876 0.0) (10 16564.8585972851 6934.3891402715 0.0))
((0 . "LWPOLYLINE") (100 . "AcDbEntity") (8 . "PLANTS") (62 . 94) (370 . 13) (100 . "AcDbPolyline") (90 . 3) (70 . 0)
(43 . 0.0) (10 16561.0859728507 6840.1209276018) (10 16560.9285067873 6874.060520362) (10 16551.657239819
6887.254638009))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16551.657239819 6887.254638009 0.0) (10 16590.7078508349 6885.399333494 0.0) (10 16610.2157351111
6929.5568956625 0.0) (10 16651.5837104072 6923.0769230769 0.0))
((0 . "LWPOLYLINE") (100 . "AcDbEntity") (8 . "PLANTS") (62 . 94) (370 . 13) (100 . "AcDbPolyline") (90 . 3) (70 . 0)
(43 . 0.0) (10 16553.5463800905 312.9722850679) (10 16553.6996606335 282.8054298643) (10 16564.8585972851
267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16553.5463800905 312.9722850679 0.0) (10 16590.0354902935 339.9879553669 0.0) (10 16546.7134306955
400.8781552074 0.0) (10 16587.4830316742 429.8642533937 0.0))
((0 . "LWPOLYLINE") (100 . "AcDbEntity") (8 . "PLANTS") (62 . 94) (370 . 13) (100 . "AcDbPolyline") (90 . 3) (70 . 0)
(43 . 0.0) (10 16561.0859728507 6840.1209276018) (10 16610.0990950226 6840.2687782805) (10 16617.6470588235
6843.8914027149))
((0 . "LWPOLYLINE") (100 . "AcDbEntity") (8 . "PLANTS") (62 . 94) (370 . 13) (100 . "AcDbPolyline") (90 . 2) (70 . 0)
(43 . 0.0) (10 16564.8585972851 6972.0962669683) (10 16564.8585972851 6934.3891402715))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5938710034) (40
. 1) (40 . 1) (40 . 1) (40 . 1) (10 16564.8585972851 6972.0962669683 0.0) (10 16582.7849691135 6968.9814405829 0.0) (10
16605.1019490146 7014.1620268162 0.0) (10 16639.1566847992 6979.7438457712 0.0) (10 16632.7319004525 6964.5553167421
0.0))
((0 . "LWPOLYLINE") (100 . "AcDbEntity") (8 . "PLANTS") (62 . 94) (370 . 13) (100 . "AcDbPolyline") (90 . 2) (70 . 0)
(43 . 0.0) (10 16583.7104072398 6930.6186651584) (10 16564.8585972851 6934.3891402715))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16591.25 493.967760181 0.0) (10 16565.5207415742 502.825828596 0.0) (10 16561.684613416 532.0348860485
0.0) (10 16564.8585972851 554.2986425339 0.0))
((0 . "LWPOLYLINE") (100 . "AcDbEntity") (8 . "PLANTS") (62 . 94) (370 . 13) (100 . "AcDbPolyline") (90 . 3) (70 . 0)
(43 . 0.0) (10 16564.8585972851 554.2986425339) (10 16596.078959276 674.9632352941) (10 16601.3357091304
686.9819955714))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16664.8121839299 806.6908105145 0.0) (10 16678.5298861235 818.2858622644 0.0) (10 16685.8377837466
845.131170485 0.0) (10 16705.0462324679 851.3591056711 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16721.8213813747 815.0129497059 0.0) (10 16719.0590629638 746.5154706738 0.0) (10 16675.0457073098
684.3461769536 0.0) (10 16677.9807692307 614.6295248869 0.0))
((0 . "LWPOLYLINE") (100 . "AcDbEntity") (8 . "PLANTS") (62 . 94) (370 . 13) (100 . "AcDbPolyline") (90 . 2) (70 . 0)
(43 . 0.0) (10 16564.8585972851 267.7234162896) (10 16572.3981900452 267.7234162896))
((0 . "LWPOLYLINE") (100 . "AcDbEntity") (8 . "PLANTS") (62 . 94) (370 . 13) (100 . "AcDbPolyline") (90 . 3) (70 . 0)
(43 . 0.0) (10 16628.9592760181 241.3263574661) (10 16595.0226244344 242.5312217195) (10 16572.3981900452
267.7234162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16617.6470588235 312.9722850679 0.0) (10 16617.3195216979 282.2537536617 0.0) (10 16583.0110366548
289.7090706488 0.0) (10 16572.3981900452 267.7234162896 0.0))
((0 . "LWPOLYLINE") (100 . "AcDbEntity") (8 . "PLANTS") (62 . 94) (370 . 13) (100 . "AcDbPolyline") (90 . 2) (70 . 0)
(43 . 0.0) (10 16587.4830316742 429.8642533937) (10 16640.2714932127 418.5520361991))
((0 . "LWPOLYLINE") (100 . "AcDbEntity") (8 . "PLANTS") (62 . 94) (370 . 13) (100 . "AcDbPolyline") (90 . 2) (70 . 0)
(43 . 0.0) (10 16591.25 493.967760181) (10 16587.4830316742 429.8642533937))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16591.25 493.967760181 0.0) (10 16632.8532814689 480.8162415117 0.0) (10 16629.0151836025 526.5336899806
0.0) (10 16655.3563348416 535.4440045249 0.0))
((0 . "LWPOLYLINE") (100 . "AcDbEntity") (8 . "PLANTS") (62 . 94) (370 . 13) (100 . "AcDbPolyline") (90 . 2) (70 . 0)
(43 . 0.0) (10 16610.1074660633 554.2986425339) (10 16602.5622171946 546.7562217195))
((0 . "LWPOLYLINE") (100 . "AcDbEntity") (8 . "PLANTS") (62 . 94) (370 . 13) (100 . "AcDbPolyline") (90 . 2) (70 . 0)
(43 . 0.0) (10 16613.8744343891 569.3806561086) (10 16610.1074660633 580.6928733032))
((0 . "LWPOLYLINE") (100 . "AcDbEntity") (8 . "PLANTS") (62 . 94) (370 . 13) (100 . "AcDbPolyline") (90 . 2) (70 . 0)
(43 . 0.0) (10 16632.7319004525 6964.5553167421) (10 16613.8744343891 6953.2430995475))
((0 . "LWPOLYLINE") (100 . "AcDbEntity") (8 . "PLANTS") (62 . 94) (370 . 13) (100 . "AcDbPolyline") (90 . 2) (70 . 0)
(43 . 0.0) (10 16617.6470588235 6843.8914027149) (10 16651.5837104072 6843.8914027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16617.6470588235 6843.8914027149 0.0) (10 16613.0281206125 6865.9651794638 0.0) (10 16641.5402946312
6895.0112129954 0.0) (10 16662.8959276018 6881.5985294118 0.0))
((0 . "LWPOLYLINE") (100 . "AcDbEntity") (8 . "PLANTS") (62 . 94) (370 . 13) (100 . "AcDbPolyline") (90 . 2) (70 . 0)
(43 . 0.0) (10 16625.1866515837 316.742081448) (10 16617.6470588235 320.5118778281))
((0 . "LWPOLYLINE") (100 . "AcDbEntity") (8 . "PLANTS") (62 . 94) (370 . 13) (100 . "AcDbPolyline") (90 . 2) (70 . 0)
(43 . 0.0) (10 16617.6470588235 312.9722850679) (10 16617.6470588235 320.5118778281))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16649.7002262443 401.5837104072 0.0) (10 16650.411800848 381.5945800692 0.0) (10 16599.7999949441
348.8006927332 0.0) (10 16617.6470588235 320.5118778281 0.0))
((0 . "LWPOLYLINE") (100 . "AcDbEntity") (8 . "PLANTS") (62 . 94) (370 . 13) (100 . "AcDbPolyline") (90 . 2) (70 . 0)
(43 . 0.0) (10 16625.1866515837 316.742081448) (10 16617.6470588235 312.9722850679))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16625.1866515837 316.742081448 0.0) (10 16643.882989307 315.481658759 0.0) (10 16647.6853726607
343.045762 0.0) (10 16666.6685520362 343.1363122172 0.0))
((0 . "LWPOLYLINE") (100 . "AcDbEntity") (8 . "PLANTS") (62 . 94) (370 . 13) (100 . "AcDbPolyline") (90 . 2) (70 . 0)
(43 . 0.0) (10 16636.4988687783 629.7143665158) (10 16628.9592760181 625.9417420814))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16726.9966063349 245.0989819004 0.0) (10 16700.5397480626 222.8831360173 0.0) (10 16657.7005977913
223.3352842688 0.0) (10 16628.9592760181 241.3263574661 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16681.7477375566 328.0542986425 0.0) (10 16675.3136067631 292.0423166869 0.0) (10 16630.4944287068
278.4003609968 0.0) (10 16628.9592760181 241.3263574661 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16632.7319004525 6964.5553167421 0.0) (10 16649.7108076103 6923.4342610928 0.0) (10 16689.9110858846
6939.4370683842 0.0) (10 16715.6843891403 6953.2430995475 0.0))
((0 . "LWPOLYLINE") (100 . "AcDbEntity") (8 . "PLANTS") (62 . 94) (370 . 13) (100 . "AcDbPolyline") (90 . 3) (70 . 0)
(43 . 0.0) (10 16649.7002262443 401.5837104072) (10 16640.2714932127 411.0096153846) (10 16640.2714932127
418.5520361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16685.520361991 527.9044117647 0.0) (10 16686.9464202253 484.9066129613 0.0) (10 16649.4206724938
458.0219806182 0.0) (10 16640.2714932127 418.5520361991 0.0))
((0 . "LWPOLYLINE") (100 . "AcDbEntity") (8 . "PLANTS") (62 . 94) (370 . 13) (100 . "AcDbPolyline") (90 . 2) (70 . 0)
(43 . 0.0) (10 16674.2081447964 373.3031674208) (10 16649.7002262443 401.5837104072))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16715.6843891403 471.3433257919 0.0) (10 16680.6535912644 462.8716085252 0.0) (10 16684.3770068809
413.1203971457 0.0) (10 16649.7002262443 401.5837104072 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16715.6843891403 6840.1209276018 0.0) (10 16697.0401269485 6828.8891643577 0.0) (10 16667.8375600049
6828.0215627976 0.0) (10 16651.5837104072 6843.8914027149 0.0))
((0 . "LWPOLYLINE") (100 . "AcDbEntity") (8 . "PLANTS") (62 . 94) (370 . 13) (100 . "AcDbPolyline") (90 . 2) (70 . 0)
(43 . 0.0) (10 16662.8959276018 6881.5985294118) (10 16651.5837104072 6843.8914027149))
((0 . "LWPOLYLINE") (100 . "AcDbEntity") (8 . "PLANTS") (62 . 94) (370 . 13) (100 . "AcDbPolyline") (90 . 2) (70 . 0)
(43 . 0.0) (10 16685.520361991 527.9044117647) (10 16655.3563348416 535.4440045249))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16655.3563348416 535.4440045249 0.0) (10 16651.9353398317 563.6037853297 0.0) (10 16666.1096620764
590.3133741868 0.0) (10 16677.9807692308 614.6295248869 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16715.6843891403 6953.2430995475 0.0) (10 16719.7302287763 6988.5003631477 0.0) (10 16682.9310901011
6992.6704290282 0.0) (10 16659.1233031674 6990.9502262443 0.0))
((0 . "LWPOLYLINE") (100 . "AcDbEntity") (8 . "PLANTS") (62 . 94) (370 . 13) (100 . "AcDbPolyline") (90 . 2) (70 . 0)
(43 . 0.0) (10 16662.8959276018 6881.5985294118) (10 16711.9174208145 6889.1402714932))
((0 . "LWPOLYLINE") (100 . "AcDbEntity") (8 . "PLANTS") (62 . 94) (370 . 13) (100 . "AcDbPolyline") (90 . 2) (70 . 0)
(43 . 0.0) (10 16681.7477375566 328.0542986425) (10 16666.6685520362 343.1363122172))
((0 . "LWPOLYLINE") (100 . "AcDbEntity") (8 . "PLANTS") (62 . 94) (370 . 13) (100 . "AcDbPolyline") (90 . 2) (70 . 0)
(43 . 0.0) (10 16674.2081447964 373.3031674208) (10 16666.6685520362 343.1363122172))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4012853704) (40
. 1) (40 . 1) (40 . 1) (40 . 1) (10 16674.2081447963 7107.8428733033 0.0) (10 16666.8423480517 7085.453701608 0.0) (10
16699.2568590003 7056.872269319 0.0) (10 16753.9712121951 7076.3115067543 0.0) (10 16760.9332579186 7036.1990950226
0.0))
((0 . "LWPOLYLINE") (100 . "AcDbEntity") (8 . "PLANTS") (62 . 94) (370 . 13) (100 . "AcDbPolyline") (90 . 2) (70 . 0)
(43 . 0.0) (10 16674.2081447964 373.3031674208) (10 16696.8325791855 377.0729638009))
((0 . "LWPOLYLINE") (100 . "AcDbEntity") (8 . "PLANTS") (62 . 94) (370 . 13) (100 . "AcDbPolyline") (90 . 3) (70 . 0)
(43 . 0.0) (10 16693.0599547511 618.4021493213) (10 16689.2929864253 614.6295248869) (10 16677.9807692308
614.6295248869))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16681.7477375566 328.0542986425 0.0) (10 16725.107746081 325.175150404 0.0) (10 16703.2582043337
267.333474421 0.0) (10 16726.9966063348 245.0989819005 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16685.520361991 527.9044117647 0.0) (10 16722.9952135732 562.4095171084 0.0) (10 16751.943390355
618.4814759656 0.0) (10 16804.0002926225 636.9586420027 0.0))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.1409193884)
(40 . 0.1624007239) (40 . 0.2494864647) (40 . 1) (40 . 1) (40 . 1) (40 . 1) (10 16862.4769537448 666.1174877582 0.0) (10
16871.3197048284 672.5455004517 0.0) (10 16899.7099389033 685.9201572486 0.0) (10 16909.616953014 671.9930062072 0.0)
(10 16865.0116282886 578.3024189174 0.0) (10 16815.2422218824 517.5814806761 0.0) (10 16749.621040724 467.5707013575
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16757.1662895927 312.9722850679 0.0) (10 16735.033028065 334.0307144324 0.0) (10 16737.0197554006
375.0352598778 0.0) (10 16696.8325791855 377.0729638009 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16753.3936651584 433.6340497738 0.0) (10 16736.2145256321 417.4657073397 0.0) (10 16699.5576828762
406.3851942734 0.0) (10 16696.8325791855 377.0729638009 0.0))
((0 . "LWPOLYLINE") (100 . "AcDbEntity") (8 . "PLANTS") (62 . 94) (370 . 13) (100 . "AcDbPolyline") (90 . 2) (70 . 0)
(43 . 0.0) (10 16715.6843891403 6757.1641402715) (10 16708.1447963801 6783.559841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16715.6843891403 6840.1209276018 0.0) (10 16735.5568039506 6823.4788571497 0.0) (10 16726.2561368768
6795.1114949769 0.0) (10 16708.1447963801 6783.559841629 0.0))
((0 . "LWPOLYLINE") (100 . "AcDbEntity") (8 . "PLANTS") (62 . 94) (370 . 13) (100 . "AcDbPolyline") (90 . 2) (70 . 0)
(43 . 0.0) (10 16719.4570135747 6862.745361991) (10 16711.9174208145 6889.1402714932))
((0 . "LWPOLYLINE") (100 . "AcDbEntity") (8 . "PLANTS") (62 . 94) (370 . 13) (100 . "AcDbPolyline") (90 . 3) (70 . 0)
(43 . 0.0) (10 16745.8540723982 6930.6186651584) (10 16741.0251131222 6911.9130090498) (10 16711.9174208145
6889.1402714932))
((0 . "LWPOLYLINE") (100 . "AcDbEntity") (8 . "PLANTS") (62 . 94) (370 . 13) (100 . "AcDbPolyline") (90 . 2) (70 . 0)
(43 . 0.0) (10 16782.0866409785 6489.4418552036) (10 16862.7432126697 6489.4418552036))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16809.9547511312 6975.8675339367 0.0) (10 16773.5764596158 6966.7040862063 0.0) (10 16734.3456346338
6986.2174843229 0.0) (10 16715.6843891403 7017.3451357466 0.0))
((0 . "LWPOLYLINE") (100 . "AcDbEntity") (8 . "PLANTS") (62 . 94) (370 . 13) (100 . "AcDbPolyline") (90 . 3) (70 . 0)
(43 . 0.0) (10 16745.8540723982 6930.6186651584) (10 16734.5334841629 6948.4158371041) (10 16715.6843891403
6953.2430995475))
((0 . "LWPOLYLINE") (100 . "AcDbEntity") (8 . "PLANTS") (62 . 94) (370 . 13) (100 . "AcDbPolyline") (90 . 2) (70 . 0)
(43 . 0.0) (10 16715.6843891403 6840.1209276018) (10 16719.4570135747 6862.745361991))
((0 . "LWPOLYLINE") (100 . "AcDbEntity") (8 . "PLANTS") (62 . 94) (370 . 13) (100 . "AcDbPolyline") (90 . 2) (70 . 0)
(43 . 0.0) (10 16715.6843891403 6757.1641402715) (10 16704.0701010611 6730.7692307692))
((0 . "LWPOLYLINE") (100 . "AcDbEntity") (8 . "PLANTS") (62 . 94) (370 . 13) (100 . "AcDbPolyline") (90 . 2) (70 . 0)
(43 . 0.0) (10 16715.6843891403 6757.1641402715) (10 16753.3936651584 6760.9354072398))
((0 . "LWPOLYLINE") (100 . "AcDbEntity") (8 . "PLANTS") (62 . 94) (370 . 13) (100 . "AcDbPolyline") (90 . 2) (70 . 0)
(43 . 0.0) (10 16715.6843891403 471.3433257919) (10 16749.621040724 467.5707013575))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16715.6843891403 471.3433257919 0.0) (10 16724.580860501 529.2502926508 0.0) (10 16790.6726124631
558.4662449873 0.0) (10 16820.9097225629 600.3215437986 0.0))
((0 . "LWPOLYLINE") (100 . "AcDbEntity") (8 . "PLANTS") (62 . 94) (370 . 13) (100 . "AcDbPolyline") (90 . 2) (70 . 0)
(43 . 0.0) (10 16822.9808605927 602.3161065125) (10 16851.4309954751 629.7143665158))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16719.4570135747 6862.7453619909 0.0) (10 16755.9152008418 6856.2486700079 0.0) (10 16769.7255904449
6903.1731536853 0.0) (10 16806.1821266968 6896.6820135747 0.0))
((0 . "LWPOLYLINE") (100 . "AcDbEntity") (8 . "PLANTS") (62 . 94) (370 . 13) (100 . "AcDbPolyline") (90 . 3) (70 . 0)
(43 . 0.0) (10 16779.7907239819 256.411199095) (10 16764.7058823529 245.2522624434) (10 16726.9966063348
245.0989819005))
((0 . "LWPOLYLINE") (100 . "AcDbEntity") (8 . "PLANTS") (62 . 94) (370 . 13) (100 . "AcDbPolyline") (90 . 3) (70 . 0)
(43 . 0.0) (10 16745.8540723982 6930.6186651584) (10 16798.6425339367 6943.1283936652) (10 16813.7273755656
6957.0135746606))
((0 . "LWPOLYLINE") (100 . "AcDbEntity") (8 . "PLANTS") (62 . 94) (370 . 13) (100 . "AcDbPolyline") (90 . 2) (70 . 0)
(43 . 0.0) (10 16749.621040724 467.5707013575) (10 16753.3936651584 444.9462669683))
((0 . "LWPOLYLINE") (100 . "AcDbEntity") (8 . "PLANTS") (62 . 94) (370 . 13) (100 . "AcDbPolyline") (90 . 2) (70 . 0)
(43 . 0.0) (10 16760.9332579186 6715.6865384615) (10 16753.3936651584 6760.9354072398))
((0 . "LWPOLYLINE") (100 . "AcDbEntity") (8 . "PLANTS") (62 . 94) (370 . 13) (100 . "AcDbPolyline") (90 . 3) (70 . 0)
(43 . 0.0) (10 16783.5576923077 6779.7885746606) (10 16764.7127828054 6774.9621040724) (10 16753.3936651584
6760.9354072398))
((0 . "LWPOLYLINE") (100 . "AcDbEntity") (8 . "PLANTS") (62 . 94) (370 . 13) (100 . "AcDbPolyline") (90 . 2) (70 . 0)
(43 . 0.0) (10 16757.6953733302 6712.4477308453) (10 16760.9332579186 6715.6865384615))
((0 . "LWPOLYLINE") (100 . "AcDbEntity") (8 . "PLANTS") (62 . 94) (370 . 13) (100 . "AcDbPolyline") (90 . 2) (70 . 0)
(43 . 0.0) (10 16753.3936651584 433.6340497738) (10 16753.3936651584 444.9462669683))
((0 . "LWPOLYLINE") (100 . "AcDbEntity") (8 . "PLANTS") (62 . 94) (370 . 13) (100 . "AcDbPolyline") (90 . 2) (70 . 0)
(43 . 0.0) (10 16779.7907239819 448.7188914027) (10 16753.3936651584 444.9462669683))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16753.3936651584 433.6340497738 0.0) (10 16775.9725079851 406.7243300574 0.0) (10 16780.3166175796
369.2414492831 0.0) (10 16779.7907239819 335.596719457 0.0))
((0 . "LWPOLYLINE") (100 . "AcDbEntity") (8 . "PLANTS") (62 . 94) (370 . 13) (100 . "AcDbPolyline") (90 . 3) (70 . 0)
(43 . 0.0) (10 16761.034065295 6681.9225471675) (10 16772.2454751131 6671.4936651584) (10 16783.5576923077
6666.6664027149))
((0 . "LWPOLYLINE") (100 . "AcDbEntity") (8 . "PLANTS") (62 . 94) (370 . 13) (100 . "AcDbPolyline") (90 . 3) (70 . 0)
(43 . 0.0) (10 16779.7907239819 263.9507918552) (10 16765.9100678733 275.2630090498) (10 16757.1662895928
312.9722850679))
((0 . "LWPOLYLINE") (100 . "AcDbEntity") (8 . "PLANTS") (62 . 94) (370 . 13) (100 . "AcDbPolyline") (90 . 3) (70 . 0)
(43 . 0.0) (10 16757.1662895928 312.9722850679) (10 16772.0990950226 321.5627828054) (10 16779.7907239819
335.596719457))
((0 . "LWPOLYLINE") (100 . "AcDbEntity") (8 . "PLANTS") (62 . 94) (370 . 13) (100 . "AcDbPolyline") (90 . 2) (70 . 0)
(43 . 0.0) (10 16760.9332579186 6817.4964932127) (10 16779.7907239819 6817.4964932127))
((0 . "LWPOLYLINE") (100 . "AcDbEntity") (8 . "PLANTS") (62 . 94) (370 . 13) (100 . "AcDbPolyline") (90 . 2) (70 . 0)
(43 . 0.0) (10 16779.7907239819 6715.6865384615) (10 16760.9332579186 6715.6865384615))
((0 . "LWPOLYLINE") (100 . "AcDbEntity") (8 . "PLANTS") (62 . 94) (370 . 13) (100 . "AcDbPolyline") (90 . 2) (70 . 0)
(43 . 0.0) (10 16760.9332579186 723.9819004525) (10 16763.8357117995 723.9819004525))
((0 . "LWPOLYLINE") (100 . "AcDbEntity") (8 . "PLANTS") (62 . 94) (370 . 13) (100 . "AcDbPolyline") (90 . 3) (70 . 0)
(43 . 0.0) (10 16770.7397618401 6593.1847501831) (10 16786.1261312217 6606.334841629) (10 16791.1029411765
6647.8132352941))
((0 . "LWPOLYLINE") (100 . "AcDbEntity") (8 . "PLANTS") (62 . 94) (370 . 13) (100 . "AcDbPolyline") (90 . 2) (70 . 0)
(43 . 0.0) (10 16928.5814779576 772.901719179) (10 16968.3257918552 772.8737839955))
((0 . "LWPOLYLINE") (100 . "AcDbEntity") (8 . "PLANTS") (62 . 94) (370 . 13) (100 . "AcDbPolyline") (90 . 2) (70 . 0)
(43 . 0.0) (10 16783.5576923077 6779.7885746606) (10 16779.7907239819 6817.4964932127))
((0 . "LWPOLYLINE") (100 . "AcDbEntity") (8 . "PLANTS") (62 . 94) (370 . 13) (100 . "AcDbPolyline") (90 . 3) (70 . 0)
(43 . 0.0) (10 16779.7907239819 6817.4964932127) (10 16787.3372171946 6832.5726244344) (10 16813.7273755656
6851.4331447964))
((0 . "LWPOLYLINE") (100 . "AcDbEntity") (8 . "PLANTS") (62 . 94) (370 . 13) (100 . "AcDbPolyline") (90 . 3) (70 . 0)
(43 . 0.0) (10 16791.1029411765 6689.2908371041) (10 16789.89739819 6704.3739819005) (10 16779.7907239819
6715.6865384615))
((0 . "LWPOLYLINE") (100 . "AcDbEntity") (8 . "PLANTS") (62 . 94) (370 . 13) (100 . "AcDbPolyline") (90 . 2) (70 . 0)
(43 . 0.0) (10 16779.7907239819 6715.6865384615) (10 16791.1029411765 6723.2274886878))
((0 . "LWPOLYLINE") (100 . "AcDbEntity") (8 . "PLANTS") (62 . 94) (370 . 13) (100 . "AcDbPolyline") (90 . 2) (70 . 0)
(43 . 0.0) (10 16806.1821266968 324.2845022624) (10 16779.7907239819 335.596719457))
((0 . "LWPOLYLINE") (100 . "AcDbEntity") (8 . "PLANTS") (62 . 94) (370 . 13) (100 . "AcDbPolyline") (90 . 3) (70 . 0)
(43 . 0.0) (10 16779.7907239819 263.9507918552) (10 16787.3303167421 260.1809954751) (10 16787.3303167421
256.411199095))
((0 . "LWPOLYLINE") (100 . "AcDbEntity") (8 . "PLANTS") (62 . 94) (370 . 13) (100 . "AcDbPolyline") (90 . 2) (70 . 0)
(43 . 0.0) (10 16779.7907239819 256.411199095) (10 16779.7907239819 263.9507918552))
((0 . "LWPOLYLINE") (100 . "AcDbEntity") (8 . "PLANTS") (62 . 94) (370 . 13) (100 . "AcDbPolyline") (90 . 2) (70 . 0)
(43 . 0.0) (10 16779.7907239819 256.411199095) (10 16787.3303167421 256.411199095))
((0 . "LWPOLYLINE") (100 . "AcDbEntity") (8 . "PLANTS") (62 . 94) (370 . 13) (100 . "AcDbPolyline") (90 . 2) (70 . 0)
(43 . 0.0) (10 16843.8914027149 6777.9037330317) (10 16783.5576923077 6779.7885746606))
((0 . "LWPOLYLINE") (100 . "AcDbEntity") (8 . "PLANTS") (62 . 94) (370 . 13) (100 . "AcDbPolyline") (90 . 3) (70 . 0)
(43 . 0.0) (10 16791.1029411765 6647.8132352941) (10 16784.7563348416 6655.3607466063) (10 16783.5576923077
6666.6664027149))
((0 . "LWPOLYLINE") (100 . "AcDbEntity") (8 . "PLANTS") (62 . 94) (370 . 13) (100 . "AcDbPolyline") (90 . 2) (70 . 0)
(43 . 0.0) (10 16791.1029411765 6677.9786199095) (10 16783.5576923077 6666.6664027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16787.3303167421 7013.5746606335 0.0) (10 16807.9001322716 7015.1586062149 0.0) (10 16793.283491116
6986.7595314818 0.0) (10 16809.9547511312 6983.4084841629 0.0))
((0 . "LWPOLYLINE") (100 . "AcDbEntity") (8 . "PLANTS") (62 . 94) (370 . 13) (100 . "AcDbPolyline") (90 . 2) (70 . 0)
(43 . 0.0) (10 16794.8699095023 256.411199095) (10 16787.3303167421 256.411199095))
((0 . "LWPOLYLINE") (100 . "AcDbEntity") (8 . "PLANTS") (62 . 94) (370 . 13) (100 . "AcDbPolyline") (90 . 2) (70 . 0)
(43 . 0.0) (10 16821.2669683258 6651.5837104072) (10 16791.1029411765 6647.8132352941))
((0 . "LWPOLYLINE") (100 . "AcDbEntity") (8 . "PLANTS") (62 . 94) (370 . 13) (100 . "AcDbPolyline") (90 . 3) (70 . 0)
(43 . 0.0) (10 16794.8699095023 256.411199095) (10 16806.1821266968 249.0234162896) (10 16828.806561086 248.8687782805))
((0 . "LWPOLYLINE") (100 . "AcDbEntity") (8 . "PLANTS") (62 . 94) (370 . 13) (100 . "AcDbPolyline") (90 . 2) (70 . 0)
(43 . 0.0) (10 16794.8699095023 256.411199095) (10 16802.415158371 271.4932126697))
((0 . "LWPOLYLINE") (100 . "AcDbEntity") (8 . "PLANTS") (62 . 94) (370 . 13) (100 . "AcDbPolyline") (90 . 2) (70 . 0)
(43 . 0.0) (10 16802.415158371 271.4932126697) (10 16806.1821266968 324.2845022624))
((0 . "LWPOLYLINE") (100 . "AcDbEntity") (8 . "PLANTS") (62 . 94) (370 . 13) (100 . "AcDbPolyline") (90 . 3) (70 . 0)
(43 . 0.0) (10 16802.415158371 271.4932126697) (10 16809.9616515837 272.6980769231) (10 16836.3518099548
290.3478506787))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16809.9547511312 6983.4084841629 0.0) (10 16855.3135973861 7000.4894569268 0.0) (10 16806.8235237343
7030.598761257 0.0) (10 16806.1821266968 7055.0530542986 0.0))
((0 . "LWPOLYLINE") (100 . "AcDbEntity") (8 . "PLANTS") (62 . 94) (370 . 13) (100 . "AcDbPolyline") (90 . 2) (70 . 0)
(43 . 0.0) (10 16813.7273755656 6851.4331447964) (10 16806.1821266968 6896.6820135747))
((0 . "LWPOLYLINE") (100 . "AcDbEntity") (8 . "PLANTS") (62 . 94) (370 . 13) (100 . "AcDbPolyline") (90 . 3) (70 . 0)
(43 . 0.0) (10 16840.1187782805 6938.1596153846) (10 16828.653280543 6911.7712669683) (10 16806.1821266968
6896.6820135747))
((0 . "LWPOLYLINE") (100 . "AcDbEntity") (8 . "PLANTS") (62 . 94) (370 . 13) (100 . "AcDbPolyline") (90 . 2) (70 . 0)
(43 . 0.0) (10 16836.3518099548 328.0542986425) (10 16806.1821266968 324.2845022624))
((0 . "LWPOLYLINE") (100 . "AcDbEntity") (8 . "PLANTS") (62 . 94) (370 . 13) (100 . "AcDbPolyline") (90 . 2) (70 . 0)
(43 . 0.0) (10 16809.9547511312 6975.8675339367) (10 16809.9547511312 6983.4084841629))
((0 . "LWPOLYLINE") (100 . "AcDbEntity") (8 . "PLANTS") (62 . 94) (370 . 13) (100 . "AcDbPolyline") (90 . 2) (70 . 0)
(43 . 0.0) (10 16809.9547511312 6975.8675339367) (10 16813.7273755656 6957.0135746606))
((0 . "LWPOLYLINE") (100 . "AcDbEntity") (8 . "PLANTS") (62 . 94) (370 . 13) (100 . "AcDbPolyline") (90 . 3) (70 . 0)
(43 . 0.0) (10 16809.9547511312 441.1764705882) (10 16825.0395927602 436.3495475113) (10 16836.3518099548
426.0944570136))
((0 . "LWPOLYLINE") (100 . "AcDbEntity") (8 . "PLANTS") (62 . 94) (370 . 13) (100 . "AcDbPolyline") (90 . 3) (70 . 0)
(43 . 0.0) (10 16813.7273755656 6957.0135746606) (10 16821.2738687783 6955.8092760181) (10 16840.1187782805
6938.1596153846))
((0 . "LWPOLYLINE") (100 . "AcDbEntity") (8 . "PLANTS") (62 . 94) (370 . 13) (100 . "AcDbPolyline") (90 . 2) (70 . 0)
(43 . 0.0) (10 16847.6640271493 6851.4331447964) (10 16813.7273755656 6851.4331447964))
((0 . "LWPOLYLINE") (100 . "AcDbEntity") (8 . "PLANTS") (62 . 94) (370 . 13) (100 . "AcDbPolyline") (90 . 2) (70 . 0)
(43 . 0.0) (10 16843.8914027149 6606.334841629) (10 16821.2669683258 6651.5837104072))
((0 . "LWPOLYLINE") (100 . "AcDbEntity") (8 . "PLANTS") (62 . 94) (370 . 13) (100 . "AcDbPolyline") (90 . 2) (70 . 0)
(43 . 0.0) (10 16821.2669683258 6651.5837104072) (10 16832.5791855204 6685.520361991))
((0 . "LWPOLYLINE") (100 . "AcDbEntity") (8 . "PLANTS") (62 . 94) (370 . 13) (100 . "AcDbPolyline") (90 . 2) (70 . 0)
(43 . 0.0) (10 16825.0395927602 6696.8325791855) (10 16832.5791855204 6685.520361991))
((0 . "LWPOLYLINE") (100 . "AcDbEntity") (8 . "PLANTS") (62 . 94) (370 . 13) (100 . "AcDbPolyline") (90 . 2) (70 . 0)
(43 . 0.0) (10 16825.0395927602 6595.0226244344) (10 16843.8914027149 6606.334841629))
((0 . "LWPOLYLINE") (100 . "AcDbEntity") (8 . "PLANTS") (62 . 94) (370 . 13) (100 . "AcDbPolyline") (90 . 2) (70 . 0)
(43 . 0.0) (10 16836.3518099548 6447.963800905) (10 16825.0395927602 6406.4857466063))
((0 . "LWPOLYLINE") (100 . "AcDbEntity") (8 . "PLANTS") (62 . 94) (370 . 13) (100 . "AcDbPolyline") (90 . 2) (70 . 0)
(43 . 0.0) (10 16843.8914027149 6734.5397058824) (10 16828.806561086 6730.7692307692))
((0 . "LWPOLYLINE") (100 . "AcDbEntity") (8 . "PLANTS") (62 . 94) (370 . 13) (100 . "AcDbPolyline") (90 . 2) (70 . 0)
(43 . 0.0) (10 16836.3518099548 6542.2320135747) (10 16828.806561086 6538.4615384615))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16919.3042986425 245.0989819004 0.0) (10 16901.4096799106 218.0103263703 0.0) (10 16840.7592494665
216.2440249367 0.0) (10 16828.8065610859 248.8687782805 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16828.806561086 248.8687782805 0.0) (10 16849.0967423233 250.4086779515 0.0) (10 16854.495414467
284.8846363026 0.0) (10 16836.3518099548 290.3478506787 0.0))
((0 . "LWPOLYLINE") (100 . "AcDbEntity") (8 . "PLANTS") (62 . 94) (370 . 13) (100 . "AcDbPolyline") (90 . 2) (70 . 0)
(43 . 0.0) (10 16832.5791855204 6685.520361991) (10 16862.7432126697 6685.520361991))
((0 . "LWPOLYLINE") (100 . "AcDbEntity") (8 . "PLANTS") (62 . 94) (370 . 13) (100 . "AcDbPolyline") (90 . 2) (70 . 0)
(43 . 0.0) (10 16840.1187782805 6342.3830316742) (10 16832.5791855204 6327.3002262443))
((0 . "LWPOLYLINE") (100 . "AcDbEntity") (8 . "PLANTS") (62 . 94) (370 . 13) (100 . "AcDbPolyline") (90 . 2) (70 . 0)
(43 . 0.0) (10 16836.3518099548 6542.2320135747) (10 16858.9762443439 6523.3788461538))
((0 . "LWPOLYLINE") (100 . "AcDbEntity") (8 . "PLANTS") (62 . 94) (370 . 13) (100 . "AcDbPolyline") (90 . 3) (70 . 0)
(43 . 0.0) (10 16836.3518099548 6542.2320135747) (10 16843.8983031674 6552.3399321267) (10 16870.2884615385
6553.5442307692))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16836.3518099548 335.596719457 0.0) (10 16806.1031435735 358.3572565955 0.0) (10 16843.5069323235
395.2598506044 0.0) (10 16836.3518099547 426.0944570136 0.0))
((0 . "LWPOLYLINE") (100 . "AcDbEntity") (8 . "PLANTS") (62 . 94) (370 . 13) (100 . "AcDbPolyline") (90 . 2) (70 . 0)
(43 . 0.0) (10 16836.3518099548 426.0944570136) (10 16889.1402714932 452.4886877828))
((0 . "LWPOLYLINE") (100 . "AcDbEntity") (8 . "PLANTS") (62 . 94) (370 . 13) (100 . "AcDbPolyline") (90 . 2) (70 . 0)
(43 . 0.0) (10 16836.3518099548 328.0542986425) (10 16836.3518099548 335.596719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16892.9128959276 403.4700226244 0.0) (10 16858.9581952956 395.2614436001 0.0) (10 16864.6868789258
351.2559706848 0.0) (10 16836.3518099548 335.596719457 0.0))
((0 . "LWPOLYLINE") (100 . "AcDbEntity") (8 . "PLANTS") (62 . 94) (370 . 13) (100 . "AcDbPolyline") (90 . 2) (70 . 0)
(43 . 0.0) (10 16836.3518099548 328.0542986425) (10 16836.3518099548 290.3478506787))
((0 . "LWPOLYLINE") (100 . "AcDbEntity") (8 . "PLANTS") (62 . 94) (370 . 13) (100 . "AcDbPolyline") (90 . 2) (70 . 0)
(43 . 0.0) (10 16902.3359728507 6932.5035067873) (10 16840.1187782805 6938.1596153846))
((0 . "LWPOLYLINE") (100 . "AcDbEntity") (8 . "PLANTS") (62 . 94) (370 . 13) (100 . "AcDbPolyline") (90 . 2) (70 . 0)
(43 . 0.0) (10 16843.8914027149 6777.9037330317) (10 16889.1402714932 6776.0180995475))
((0 . "LWPOLYLINE") (100 . "AcDbEntity") (8 . "PLANTS") (62 . 94) (370 . 13) (100 . "AcDbPolyline") (90 . 2) (70 . 0)
(43 . 0.0) (10 16843.8914027149 6777.9037330317) (10 16843.8914027149 6734.5397058824))
((0 . "LWPOLYLINE") (100 . "AcDbEntity") (8 . "PLANTS") (62 . 94) (370 . 13) (100 . "AcDbPolyline") (90 . 3) (70 . 0)
(43 . 0.0) (10 16847.6640271493 6843.8914027149) (10 16844.0391402715 6836.3430995475) (10 16843.8914027149
6777.9037330317))
((0 . "LWPOLYLINE") (100 . "AcDbEntity") (8 . "PLANTS") (62 . 94) (370 . 13) (100 . "AcDbPolyline") (90 . 2) (70 . 0)
(43 . 0.0) (10 16862.7432126697 6715.6865384615) (10 16843.8914027149 6734.5397058824))
((0 . "LWPOLYLINE") (100 . "AcDbEntity") (8 . "PLANTS") (62 . 94) (370 . 13) (100 . "AcDbPolyline") (90 . 2) (70 . 0)
(43 . 0.0) (10 16866.5158371041 6606.334841629) (10 16843.8914027149 6606.334841629))
((0 . "LWPOLYLINE") (100 . "AcDbEntity") (8 . "PLANTS") (62 . 94) (370 . 13) (100 . "AcDbPolyline") (90 . 2) (70 . 0)
(43 . 0.0) (10 16847.6640271493 6851.4331447964) (10 16847.6640271493 6843.8914027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16847.6640271493 6851.4331447964 0.0) (10 16885.2885615998 6866.6327859409 0.0) (10 16873.6548654021
6912.127928436 0.0) (10 16902.3359728507 6932.5035067873 0.0))
((0 . "LWPOLYLINE") (100 . "AcDbEntity") (8 . "PLANTS") (62 . 94) (370 . 13) (100 . "AcDbPolyline") (90 . 3) (70 . 0)
(43 . 0.0) (10 16847.6640271493 6843.8914027149) (10 16870.2884615385 6836.4979638009) (10 16889.1402714932
6836.3496606335))
((0 . "LWPOLYLINE") (100 . "AcDbEntity") (8 . "PLANTS") (62 . 94) (370 . 13) (100 . "AcDbPolyline") (90 . 2) (70 . 0)
(43 . 0.0) (10 16855.2036199095 6233.0316742081) (10 16862.7432126697 6259.4269230769))
((0 . "LWPOLYLINE") (100 . "AcDbEntity") (8 . "PLANTS") (62 . 94) (370 . 13) (100 . "AcDbPolyline") (90 . 2) (70 . 0)
(43 . 0.0) (10 16858.9762443439 7002.2624434389) (10 16858.9762443439 6979.6380090498))
((0 . "LWPOLYLINE") (100 . "AcDbEntity") (8 . "PLANTS") (62 . 94) (370 . 13) (100 . "AcDbPolyline") (90 . 2) (70 . 0)
(43 . 0.0) (10 16862.7432126697 6489.4418552036) (10 16858.9762443439 6523.3788461538))
((0 . "LWPOLYLINE") (100 . "AcDbEntity") (8 . "PLANTS") (62 . 94) (370 . 13) (100 . "AcDbPolyline") (90 . 3) (70 . 0)
(43 . 0.0) (10 16870.2884615385 6553.5442307692) (10 16865.3255656109 6530.9266968326) (10 16858.9762443439
6523.3788461538))
((0 . "LWPOLYLINE") (100 . "AcDbEntity") (8 . "PLANTS") (62 . 94) (370 . 13) (100 . "AcDbPolyline") (90 . 2) (70 . 0)
(43 . 0.0) (10 16858.9762443439 6463.0468325792) (10 16862.7432126697 6489.4418552036))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16877.8280542987 6368.778280543 0.0) (10 16834.7200545075 6380.1074465753 0.0) (10 16885.3111239109
6419.4958367773 0.0) (10 16858.9762443439 6432.8807692308 0.0))
((0 . "LWPOLYLINE") (100 . "AcDbEntity") (8 . "PLANTS") (62 . 94) (370 . 13) (100 . "AcDbPolyline") (90 . 2) (70 . 0)
(43 . 0.0) (10 16862.7432126697 6715.6865384615) (10 16885.3676470588 6715.6865384615))
((0 . "LWPOLYLINE") (100 . "AcDbEntity") (8 . "PLANTS") (62 . 94) (370 . 13) (100 . "AcDbPolyline") (90 . 2) (70 . 0)
(43 . 0.0) (10 16862.7432126697 6715.6865384615) (10 16862.7432126697 6685.520361991))
((0 . "LWPOLYLINE") (100 . "AcDbEntity") (8 . "PLANTS") (62 . 94) (370 . 13) (100 . "AcDbPolyline") (90 . 2) (70 . 0)
(43 . 0.0) (10 16866.5158371041 6681.7498868778) (10 16862.7432126697 6685.520361991))
((0 . "LWPOLYLINE") (100 . "AcDbEntity") (8 . "PLANTS") (62 . 94) (370 . 13) (100 . "AcDbPolyline") (90 . 3) (70 . 0)
(43 . 0.0) (10 16866.5158371041 6681.7498868778) (10 16862.7432126697 6681.7498868778) (10 16862.7432126697
6685.520361991))
((0 . "LWPOLYLINE") (100 . "AcDbEntity") (8 . "PLANTS") (62 . 94) (370 . 13) (100 . "AcDbPolyline") (90 . 3) (70 . 0)
(43 . 0.0) (10 16975.8653846154 6489.4418552036) (10 16915.5373303167 6485.6712669683) (10 16862.7432126697
6489.4418552036))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16866.5158371041 6606.334841629 0.0) (10 16879.7146748041 6630.1393915803 0.0) (10 16856.2895138867
6657.1422909028 0.0) (10 16866.5158371041 6681.7498868778 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16866.5158371041 6681.7498868778 0.0) (10 16890.1158778633 6669.8430064062 0.0) (10 16909.4906672209
6702.2024903091 0.0) (10 16885.3676470588 6715.6865384615 0.0))
((0 . "LWPOLYLINE") (100 . "AcDbEntity") (8 . "PLANTS") (62 . 94) (370 . 13) (100 . "AcDbPolyline") (90 . 3) (70 . 0)
(43 . 0.0) (10 16866.5158371041 6606.334841629) (10 16876.771719457 6587.4808823529) (10 16877.8280542986
6572.3981900452))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16866.5158371041 6293.3635746606 0.0) (10 16853.4193731604 6317.7745450923 0.0) (10 16889.9343570632
6342.5350933208 0.0) (10 16877.8280542986 6368.778280543 0.0))
((0 . "LWPOLYLINE") (100 . "AcDbEntity") (8 . "PLANTS") (62 . 94) (370 . 13) (100 . "AcDbPolyline") (90 . 3) (70 . 0)
(43 . 0.0) (10 16870.2884615385 6553.5442307692) (10 16871.4842760181 6568.4728506787) (10 16877.8280542986
6572.3981900452))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16874.0554298643 554.2986425339 0.0) (10 16851.9656566014 509.0910525186 0.0) (10 16906.2154578298
502.4045619136 0.0) (10 16904.2251131222 467.5707013575 0.0))
((0 . "LWPOLYLINE") (100 . "AcDbEntity") (8 . "PLANTS") (62 . 94) (370 . 13) (100 . "AcDbPolyline") (90 . 2) (70 . 0)
(43 . 0.0) (10 16874.0554298643 275.2630090498) (10 16919.3042986425 271.4932126697))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16892.9128959276 6527.149321267 0.0) (10 16899.2416084894 6542.6846515643 0.0) (10 16894.599475885
6565.4615514707 0.0) (10 16877.8280542986 6572.3981900452 0.0))
((0 . "LWPOLYLINE") (100 . "AcDbEntity") (8 . "PLANTS") (62 . 94) (370 . 13) (100 . "AcDbPolyline") (90 . 2) (70 . 0)
(43 . 0.0) (10 16885.3676470588 6372.5490950226) (10 16877.8280542986 6368.778280543))
((0 . "LWPOLYLINE") (100 . "AcDbEntity") (8 . "PLANTS") (62 . 94) (370 . 13) (100 . "AcDbPolyline") (90 . 2) (70 . 0)
(43 . 0.0) (10 16889.1402714932 6738.3109728507) (10 16885.3676470588 6715.6865384615))
((0 . "LWPOLYLINE") (100 . "AcDbEntity") (8 . "PLANTS") (62 . 94) (370 . 13) (100 . "AcDbPolyline") (90 . 3) (70 . 0)
(43 . 0.0) (10 16889.1402714932 6836.3496606335) (10 16894.1156108597 6802.4130090498) (10 16904.2251131222
6787.3303167421))
((0 . "LWPOLYLINE") (100 . "AcDbEntity") (8 . "PLANTS") (62 . 94) (370 . 13) (100 . "AcDbPolyline") (90 . 2) (70 . 0)
(43 . 0.0) (10 16889.1402714932 6836.3496606335) (10 16900.4524886878 6847.6618778281))
((0 . "LWPOLYLINE") (100 . "AcDbEntity") (8 . "PLANTS") (62 . 94) (370 . 13) (100 . "AcDbPolyline") (90 . 2) (70 . 0)
(43 . 0.0) (10 16889.1402714932 6738.3109728507) (10 16889.1402714932 6776.0180995475))
((0 . "LWPOLYLINE") (100 . "AcDbEntity") (8 . "PLANTS") (62 . 94) (370 . 13) (100 . "AcDbPolyline") (90 . 2) (70 . 0)
(43 . 0.0) (10 16889.1402714932 6776.0180995475) (10 16904.2251131222 6787.3303167421))
((0 . "LWPOLYLINE") (100 . "AcDbEntity") (8 . "PLANTS") (62 . 94) (370 . 13) (100 . "AcDbPolyline") (90 . 2) (70 . 0)
(43 . 0.0) (10 16889.1402714932 6738.3109728507) (10 16919.3042986425 6734.5397058824))
((0 . "LWPOLYLINE") (100 . "AcDbEntity") (8 . "PLANTS") (62 . 94) (370 . 13) (100 . "AcDbPolyline") (90 . 3) (70 . 0)
(43 . 0.0) (10 16892.9128959276 403.4700226244) (10 16892.7636877828 444.9414027149) (10 16889.1402714932
452.4886877828))
((0 . "LWPOLYLINE") (100 . "AcDbEntity") (8 . "PLANTS") (62 . 94) (370 . 13) (100 . "AcDbPolyline") (90 . 2) (70 . 0)
(43 . 0.0) (10 16904.2251131222 467.5707013575) (10 16889.1402714932 452.4886877828))
((0 . "LWPOLYLINE") (100 . "AcDbEntity") (8 . "PLANTS") (62 . 94) (370 . 13) (100 . "AcDbPolyline") (90 . 2) (70 . 0)
(43 . 0.0) (10 16892.9128959276 7051.2817873303) (10 16892.9128959276 7015.4602941176))
((0 . "SPLINE") (100 . "AcDbEntity") (8 . "PLANTS") (62 . 94) (370 . 13) (100 . "AcDbSpline") (70 . 0) (71 . 3) (72 .
13) (73 . 9) (74 . 0) (42 . 0.0000001) (43 . 0.0000001) (40 . 0.0) (40 . 0.0) (40 . 0.0) (40 . 0.0) (40 . 0.3095122826)
(40 . 0.4257968678) (40 . 0.4535768012) (40 . 0.6542394631) (40 . 0.8635480735) (40 . 1) (40 . 1) (40 . 1) (40 . 1) (10
16892.9128959276 7051.2817873303 0.0) (10 16872.3304729902 7070.5728850914 0.0) (10 16877.0467326057 7113.8466524272
0.0) (10 16833.6638085783 7141.4024637154 0.0) (10 16817.0773389529 7119.3317154023 0.0) (10 16851.4378411734
7078.1311865558 0.0) (10 16849.0840592429 7033.9068328565 0.0) (10 16879.1730889025 7009.3182477974 0.0) (10
16892.9128959276 7015.4602941176 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16892.9128959276 7051.2817873303 0.0) (10 16923.0370914518 7072.6387580002 0.0) (10 16905.8511287849
7114.055791681 0.0) (10 16935.7634000451 7136.0080404393 0.0))
((0 . "LWPOLYLINE") (100 . "AcDbEntity") (8 . "PLANTS") (62 . 94) (370 . 13) (100 . "AcDbPolyline") (90 . 3) (70 . 0)
(43 . 0.0) (10 16911.7647058824 6957.0135746606) (10 16897.8854072398 6968.3257918552) (10 16892.9128959276
7015.4602941176))
((0 . "LWPOLYLINE") (100 . "AcDbEntity") (8 . "PLANTS") (62 . 94) (370 . 13) (100 . "AcDbPolyline") (90 . 2) (70 . 0)
(43 . 0.0) (10 16930.6165158371 7017.3451357466) (10 16892.9128959276 7015.4602941176))
((0 . "LWPOLYLINE") (100 . "AcDbEntity") (8 . "PLANTS") (62 . 94) (370 . 13) (100 . "AcDbPolyline") (90 . 2) (70 . 0)
(43 . 0.0) (10 16900.4524886878 6847.6618778281) (10 16892.9128959276 6866.5158371041))
((0 . "LWPOLYLINE") (100 . "AcDbEntity") (8 . "PLANTS") (62 . 94) (370 . 13) (100 . "AcDbPolyline") (90 . 2) (70 . 0)
(43 . 0.0) (10 16900.4524886878 6440.42239819) (10 16892.9128959276 6455.5052036199))
((0 . "LWPOLYLINE") (100 . "AcDbEntity") (8 . "PLANTS") (62 . 94) (370 . 13) (100 . "AcDbPolyline") (90 . 2) (70 . 0)
(43 . 0.0) (10 16892.9128959276 403.4700226244) (10 16900.4524886878 403.4700226244))
((0 . "LWPOLYLINE") (100 . "AcDbEntity") (8 . "PLANTS") (62 . 94) (370 . 13) (100 . "AcDbPolyline") (90 . 3) (70 . 0)
(43 . 0.0) (10 16930.6165158371 6843.8914027149) (10 16923.0700226244 6847.5140271493) (10 16900.4524886878
6847.6618778281))
((0 . "LWPOLYLINE") (100 . "AcDbEntity") (8 . "PLANTS") (62 . 94) (370 . 13) (100 . "AcDbPolyline") (90 . 3) (70 . 0)
(43 . 0.0) (10 16919.3042986425 290.3478506787) (10 16904.3783936652 309.1996606335) (10 16900.4524886878
403.4700226244))
((0 . "LWPOLYLINE") (100 . "AcDbEntity") (8 . "PLANTS") (62 . 94) (370 . 13) (100 . "AcDbPolyline") (90 . 2) (70 . 0)
(43 . 0.0) (10 16915.5373303167 414.782239819) (10 16900.4524886878 403.4700226244))
((0 . "LWPOLYLINE") (100 . "AcDbEntity") (8 . "PLANTS") (62 . 94) (370 . 13) (100 . "AcDbPolyline") (90 . 3) (70 . 0)
(43 . 0.0) (10 16941.9287330317 6851.4331447964) (10 16921.8727375566 6911.7647058824) (10 16902.3359728507
6932.5035067873))
((0 . "LWPOLYLINE") (100 . "AcDbEntity") (8 . "PLANTS") (62 . 94) (370 . 13) (100 . "AcDbPolyline") (90 . 2) (70 . 0)
(43 . 0.0) (10 16902.3359728507 6932.5035067873) (10 16911.7647058824 6945.7013574661))
((0 . "LWPOLYLINE") (100 . "AcDbEntity") (8 . "PLANTS") (62 . 94) (370 . 13) (100 . "AcDbPolyline") (90 . 2) (70 . 0)
(43 . 0.0) (10 16911.7647058824 6787.3303167421) (10 16904.2251131222 6787.3303167421))
((0 . "LWPOLYLINE") (100 . "AcDbEntity") (8 . "PLANTS") (62 . 94) (370 . 13) (100 . "AcDbPolyline") (90 . 3) (70 . 0)
(43 . 0.0) (10 16915.5373303167 414.782239819) (10 16915.3812217195 456.2584841629) (10 16904.2251131222
467.5707013575))
((0 . "LWPOLYLINE") (100 . "AcDbEntity") (8 . "PLANTS") (62 . 94) (370 . 13) (100 . "AcDbPolyline") (90 . 2) (70 . 0)
(43 . 0.0) (10 16911.7647058824 6957.0135746606) (10 16911.7647058824 6945.7013574661))
((0 . "LWPOLYLINE") (100 . "AcDbEntity") (8 . "PLANTS") (62 . 94) (370 . 13) (100 . "AcDbPolyline") (90 . 3) (70 . 0)
(43 . 0.0) (10 16911.7647058824 6957.0135746606) (10 16925.6440045249 6972.0962669683) (10 16930.6165158371
7017.3451357466))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7809668533) (40
. 1) (40 . 1) (40 . 1) (40 . 1) (10 17024.8868778281 6896.6820135747 0.0) (10 17001.5460727776 6924.7237200236 0.0) (10
16953.2839203756 6919.1256298713 0.0) (10 16919.5454152497 6941.7093764058 0.0) (10 16911.7647058824 6945.7013574662
0.0))
((0 . "LWPOLYLINE") (100 . "AcDbEntity") (8 . "PLANTS") (62 . 94) (370 . 13) (100 . "AcDbPolyline") (90 . 3) (70 . 0)
(43 . 0.0) (10 16911.7647058824 6787.3303167421) (10 16925.7917420814 6779.6345022624) (10 16930.6165158371
6764.7058823529))
((0 . "LWPOLYLINE") (100 . "AcDbEntity") (8 . "PLANTS") (62 . 94) (370 . 13) (100 . "AcDbPolyline") (90 . 3) (70 . 0)
(43 . 0.0) (10 16911.7647058824 6787.3303167421) (10 16921.8727375566 6802.4130090498) (10 16930.6165158371
6843.8914027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16915.5373303167 414.782239819 0.0) (10 16944.7555519751 403.2035188018 0.0) (10 16918.2921383531
361.4721525055 0.0) (10 16941.9287330317 343.1363122172 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16919.3042986425 6734.5397058824 0.0) (10 16920.8880063994 6708.340577341 0.0) (10 16939.1909370519
6684.0186241731 0.0) (10 16964.5531674208 6677.9786199095 0.0))
((0 . "LWPOLYLINE") (100 . "AcDbEntity") (8 . "PLANTS") (62 . 94) (370 . 13) (100 . "AcDbPolyline") (90 . 2) (70 . 0)
(43 . 0.0) (10 16919.3042986425 6734.5397058824) (10 16930.6165158371 6764.7058823529))
((0 . "LWPOLYLINE") (100 . "AcDbEntity") (8 . "PLANTS") (62 . 94) (370 . 13) (100 . "AcDbPolyline") (90 . 2) (70 . 0)
(43 . 0.0) (10 16919.3042986425 290.3478506787) (10 16919.3042986425 271.4932126697))
((0 . "LWPOLYLINE") (100 . "AcDbEntity") (8 . "PLANTS") (62 . 94) (370 . 13) (100 . "AcDbPolyline") (90 . 3) (70 . 0)
(43 . 0.0) (10 16919.3042986425 290.3478506787) (10 16934.2414027149 301.6600678733) (10 16941.9287330317
316.742081448))
((0 . "LWPOLYLINE") (100 . "AcDbEntity") (8 . "PLANTS") (62 . 94) (370 . 13) (100 . "AcDbPolyline") (90 . 2) (70 . 0)
(43 . 0.0) (10 16919.3042986425 271.4932126697) (10 16919.3042986425 245.0989819005))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17002.2624434389 252.6385746606 0.0) (10 16986.4386840385 218.3685302033 0.0) (10 16942.0008186682
225.2566117225 0.0) (10 16919.3042986425 245.0989819005 0.0))
((0 . "LWPOLYLINE") (100 . "AcDbEntity") (8 . "PLANTS") (62 . 94) (370 . 13) (100 . "AcDbPolyline") (90 . 3) (70 . 0)
(43 . 0.0) (10 16930.6165158371 7017.3451357466) (10 16944.6519230769 7058.8235294118) (10 16957.0135746606
7119.1550904977))
((0 . "LWPOLYLINE") (100 . "AcDbEntity") (8 . "PLANTS") (62 . 94) (370 . 13) (100 . "AcDbPolyline") (90 . 2) (70 . 0)
(43 . 0.0) (10 16941.9287330317 6843.8914027149) (10 16930.6165158371 6843.8914027149))
((0 . "LWPOLYLINE") (100 . "AcDbEntity") (8 . "PLANTS") (62 . 94) (370 . 13) (100 . "AcDbPolyline") (90 . 2) (70 . 0)
(43 . 0.0) (10 16970.2092760181 6751.5080316742) (10 16930.6165158371 6764.7058823529))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16945.7013574661 6591.2521493213 0.0) (10 16947.9272307338 6602.9449927073 0.0) (10 16944.6172982098
6621.7958812207 0.0) (10 16930.6165158371 6625.188800905 0.0))
((0 . "LWPOLYLINE") (100 . "AcDbEntity") (8 . "PLANTS") (62 . 94) (370 . 13) (100 . "AcDbPolyline") (90 . 3) (70 . 0)
(43 . 0.0) (10 16945.7013574661 6591.2521493213) (10 16941.9287330317 6587.4808823529) (10 16930.6165158371
6587.4808823529))
((0 . "LWPOLYLINE") (100 . "AcDbEntity") (8 . "PLANTS") (62 . 94) (370 . 13) (100 . "AcDbPolyline") (90 . 3) (70 . 0)
(43 . 0.0) (10 16934.3891402715 576.9230769231) (10 16953.2409502262 584.317081448) (10 16968.3257918552
584.4358055764))
((0 . "LWPOLYLINE") (100 . "AcDbEntity") (8 . "PLANTS") (62 . 94) (370 . 13) (100 . "AcDbPolyline") (90 . 3) (70 . 0)
(43 . 0.0) (10 16941.9287330317 6851.4331447964) (10 17013.5746606335 6844.0462669683) (10 17043.7386877828
6866.5158371041))
((0 . "LWPOLYLINE") (100 . "AcDbEntity") (8 . "PLANTS") (62 . 94) (370 . 13) (100 . "AcDbPolyline") (90 . 2) (70 . 0)
(43 . 0.0) (10 16941.9287330317 6851.4331447964) (10 16941.9287330317 6843.8914027149))
((0 . "LWPOLYLINE") (100 . "AcDbEntity") (8 . "PLANTS") (62 . 94) (370 . 13) (100 . "AcDbPolyline") (90 . 3) (70 . 0)
(43 . 0.0) (10 16975.8653846154 6787.3303167421) (10 16952.1859728507 6832.5791855204) (10 16941.9287330317
6843.8914027149))
((0 . "LWPOLYLINE") (100 . "AcDbEntity") (8 . "PLANTS") (62 . 94) (370 . 13) (100 . "AcDbPolyline") (90 . 2) (70 . 0)
(43 . 0.0) (10 16941.9287330317 343.1363122172) (10 16941.9287330317 316.742081448))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.317491909)
(40 . 0.4770423692) (40 . 1) (40 . 1) (40 . 1) (40 . 1) (10 17009.8020361991 463.8009049774 0.0) (10 16994.3521989412
453.6543989503 0.0) (10 17000.7636558198 426.6865943538 0.0) (10 16959.2441983395 397.7583586565 0.0) (10
16969.1560677386 350.8582046055 0.0) (10 16941.9287330317 343.1363122172 0.0))
((0 . "LWPOLYLINE") (100 . "AcDbEntity") (8 . "PLANTS") (62 . 94) (370 . 13) (100 . "AcDbPolyline") (90 . 2) (70 . 0)
(43 . 0.0) (10 16987.17760181 335.596719457) (10 16941.9287330317 316.742081448))
((0 . "LWPOLYLINE") (100 . "AcDbEntity") (8 . "PLANTS") (62 . 94) (370 . 13) (100 . "AcDbPolyline") (90 . 3) (70 . 0)
(43 . 0.0) (10 16987.17760181 6576.1686651584) (10 16968.3257918552 6590.195361991) (10 16945.7013574661
6591.2521493213))
((0 . "LWPOLYLINE") (100 . "AcDbEntity") (8 . "PLANTS") (62 . 94) (370 . 13) (100 . "AcDbPolyline") (90 . 2) (70 . 0)
(43 . 0.0) (10 16968.3257918552 729.3848775268) (10 16953.2409502262 735.2941176471))
((0 . "LWPOLYLINE") (100 . "AcDbEntity") (8 . "PLANTS") (62 . 94) (370 . 13) (100 . "AcDbPolyline") (90 . 3) (70 . 0)
(43 . 0.0) (10 17017.3472850679 7088.9897058824) (10 16964.415158371 7037.4033936652) (10 16957.0135746606
7036.1990950226))
((0 . "LWPOLYLINE") (100 . "AcDbEntity") (8 . "PLANTS") (62 . 94) (370 . 13) (100 . "AcDbPolyline") (90 . 2) (70 . 0)
(43 . 0.0) (10 16975.8653846154 6655.3541855204) (10 16964.5531674208 6677.9786199095))
((0 . "LWPOLYLINE") (100 . "AcDbEntity") (8 . "PLANTS") (62 . 94) (370 . 13) (100 . "AcDbPolyline") (90 . 3) (70 . 0)
(43 . 0.0) (10 16970.2092760181 6751.5080316742) (10 16974.6626696833 6700.6030542986) (10 16964.5531674208
6677.9786199095))
((0 . "LWPOLYLINE") (100 . "AcDbEntity") (8 . "PLANTS") (62 . 94) (370 . 13) (100 . "AcDbPolyline") (90 . 3) (70 . 0)
(43 . 0.0) (10 16975.8653846154 6489.4418552036) (10 16975.7190045249 6527.149321267) (10 16968.3257918552
6542.2320135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16970.2092760181 6751.5080316742 0.0) (10 17054.250366455 6725.1112565843 0.0) (10 17147.9067258574
6748.5988796937 0.0) (10 17232.2794117647 6738.3109728507 0.0))
((0 . "LWPOLYLINE") (100 . "AcDbEntity") (8 . "PLANTS") (62 . 94) (370 . 13) (100 . "AcDbPolyline") (90 . 3) (70 . 0)
(43 . 0.0) (10 16975.8653846154 6787.3303167421) (10 16968.5480769231 6760.867760181) (10 16970.2092760181
6751.5080316742))
((0 . "LWPOLYLINE") (100 . "AcDbEntity") (8 . "PLANTS") (62 . 94) (370 . 13) (100 . "AcDbPolyline") (90 . 2) (70 . 0)
(43 . 0.0) (10 17217.1945701357 6787.3303167421) (10 16975.8653846154 6787.3303167421))
((0 . "LWPOLYLINE") (100 . "AcDbEntity") (8 . "PLANTS") (62 . 94) (370 . 13) (100 . "AcDbPolyline") (90 . 2) (70 . 0)
(43 . 0.0) (10 17018.8086214517 6489.3530328459) (10 16975.8653846154 6489.4418552036))
((0 . "LWPOLYLINE") (100 . "AcDbEntity") (8 . "PLANTS") (62 . 94) (370 . 13) (100 . "AcDbPolyline") (90 . 2) (70 . 0)
(43 . 0.0) (10 16987.17760181 335.596719457) (10 16983.4106334842 358.2211538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 16987.17760181 7028.6573529412 0.0) (10 16938.3927328434 7031.5327690793 0.0) (10 16961.3216903331
6935.7408927954 0.0) (10 16994.7228506787 6960.7840497738 0.0))
((0 . "LWPOLYLINE") (100 . "AcDbEntity") (8 . "PLANTS") (62 . 94) (370 . 13) (100 . "AcDbPolyline") (90 . 2) (70 . 0)
(43 . 0.0) (10 16987.17760181 335.596719457) (10 16994.7228506787 335.596719457))
((0 . "LWPOLYLINE") (100 . "AcDbEntity") (8 . "PLANTS") (62 . 94) (370 . 13) (100 . "AcDbPolyline") (90 . 2) (70 . 0)
(43 . 0.0) (10 16990.9502262443 380.8455882353) (10 16990.9502262443 392.1578054299))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17024.8868778281 6896.6820135747 0.0) (10 17041.9980537144 6921.4757353128 0.0) (10 17024.8774489238
6962.8614882683 0.0) (10 16994.7228506787 6960.7840497738 0.0))
((0 . "LWPOLYLINE") (100 . "AcDbEntity") (8 . "PLANTS") (62 . 94) (370 . 13) (100 . "AcDbPolyline") (90 . 2) (70 . 0)
(43 . 0.0) (10 16998.4898190045 6979.6380090498) (10 16994.7228506787 6960.7840497738))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17002.2624434389 252.6385746606 0.0) (10 16961.6179955947 274.1125288164 0.0) (10 17000.828764355
305.6381553334 0.0) (10 16994.7228506787 335.596719457 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17062.5961538462 392.1578054299 0.0) (10 17034.8420106174 378.6117691297 0.0) (10 17030.2402106845
339.0978559736 0.0) (10 16994.7228506787 335.596719457 0.0))
((0 . "LWPOLYLINE") (100 . "AcDbEntity") (8 . "PLANTS") (62 . 94) (370 . 13) (100 . "AcDbPolyline") (90 . 2) (70 . 0)
(43 . 0.0) (10 17013.5746606335 252.6385746606) (10 17002.2624434389 252.6385746606))
((0 . "LWPOLYLINE") (100 . "AcDbEntity") (8 . "PLANTS") (62 . 94) (370 . 13) (100 . "AcDbPolyline") (90 . 3) (70 . 0)
(43 . 0.0) (10 17062.5942307692 6994.7207013575) (10 17036.1990950226 6994.5728506787) (10 17013.5746606335
6983.4084841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17013.5746606335 252.6385746606 0.0) (10 17049.0827791586 191.5336613166 0.0) (10 17134.2744503415
265.7452102336 0.0) (10 17174.3930829934 215.0272411127 0.0))
((0 . "LWPOLYLINE") (100 . "AcDbEntity") (8 . "PLANTS") (62 . 94) (370 . 13) (100 . "AcDbPolyline") (90 . 2) (70 . 0)
(43 . 0.0) (10 17013.5746606335 252.6385746606) (10 17024.8868778281 271.4932126697))
((0 . "LWPOLYLINE") (100 . "AcDbEntity") (8 . "PLANTS") (62 . 94) (370 . 13) (100 . "AcDbPolyline") (90 . 2) (70 . 0)
(43 . 0.0) (10 17043.7386877828 6881.5985294118) (10 17024.8868778281 6896.6820135747))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5265053125)
(40 . 0.6447848861) (40 . 1) (40 . 1) (40 . 1) (40 . 1) (10 17122.9242081448 411.0096153846 0.0) (10 17096.9563026829
393.7861344438 0.0) (10 17075.7660487373 360.14042313 0.0) (10 17031.9255695781 320.9377134469 0.0) (10 17019.6618613357
296.2678990568 0.0) (10 17024.8868778281 271.4932126697 0.0))
((0 . "LWPOLYLINE") (100 . "AcDbEntity") (8 . "PLANTS") (62 . 94) (370 . 13) (100 . "AcDbPolyline") (90 . 2) (70 . 0)
(43 . 0.0) (10 17047.5113122172 275.2630090498) (10 17024.8868778281 271.4932126697))
((0 . "LWPOLYLINE") (100 . "AcDbEntity") (8 . "PLANTS") (62 . 94) (370 . 13) (100 . "AcDbPolyline") (90 . 2) (70 . 0)
(43 . 0.0) (10 17043.7386877828 6881.5985294118) (10 17043.7386877828 6866.5158371041))
((0 . "LWPOLYLINE") (100 . "AcDbEntity") (8 . "PLANTS") (62 . 94) (370 . 13) (100 . "AcDbPolyline") (90 . 3) (70 . 0)
(43 . 0.0) (10 17043.7386877828 6881.5985294118) (10 17061.3906108597 6900.4524886878) (10 17062.5961538462
6919.3064479638))
((0 . "LWPOLYLINE") (100 . "AcDbEntity") (8 . "PLANTS") (62 . 94) (370 . 13) (100 . "AcDbPolyline") (90 . 3) (70 . 0)
(43 . 0.0) (10 17043.7386877828 6866.5158371041) (10 17077.6753393665 6848.7121040724) (10 17115.3846153846
6847.6618778281))
((0 . "LWPOLYLINE") (100 . "AcDbEntity") (8 . "PLANTS") (62 . 94) (370 . 13) (100 . "AcDbPolyline") (90 . 2) (70 . 0)
(43 . 0.0) (10 17047.5113122172 275.2630090498) (10 17055.0509049774 271.4932126697))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17047.5113122172 275.2630090498 0.0) (10 17047.7586101024 301.2486381322 0.0) (10 17073.2155835807
319.3387559433 0.0) (10 17096.5328054299 324.2845022624 0.0))
((0 . "LWPOLYLINE") (100 . "AcDbEntity") (8 . "PLANTS") (62 . 94) (370 . 13) (100 . "AcDbPolyline") (90 . 3) (70 . 0)
(43 . 0.0) (10 17062.5942307692 7122.1719498149) (10 17062.5942307692 7017.3454751131) (10 17062.5942307692
7006.032918552))
((0 . "LWPOLYLINE") (100 . "AcDbEntity") (8 . "PLANTS") (62 . 94) (370 . 13) (100 . "AcDbPolyline") (90 . 2) (70 . 0)
(43 . 0.0) (10 17062.5942307692 6994.7207013575) (10 17062.5942307692 7006.032918552))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17171.9457013575 7077.6774886878 0.0) (10 17118.1313412355 7087.4433664685 0.0) (10 17110.992248159
7008.3786619974 0.0) (10 17062.5942307693 7006.032918552 0.0))
((0 . "LWPOLYLINE") (100 . "AcDbEntity") (8 . "PLANTS") (62 . 94) (370 . 13) (100 . "AcDbPolyline") (90 . 3) (70 . 0)
(43 . 0.0) (10 17062.5942307692 6994.7207013575) (10 17062.5942307692 6975.8675339367) (10 17062.5961538462
6919.3064479638))
((0 . "LWPOLYLINE") (100 . "AcDbEntity") (8 . "PLANTS") (62 . 94) (370 . 13) (100 . "AcDbPolyline") (90 . 3) (70 . 0)
(43 . 0.0) (10 17119.157239819 6941.9308823529) (10 17096.5328054299 6924.132918552) (10 17062.5961538462
6919.3064479638))
((0 . "LWPOLYLINE") (100 . "AcDbEntity") (8 . "PLANTS") (62 . 94) (370 . 13) (100 . "AcDbPolyline") (90 . 3) (70 . 0)
(43 . 0.0) (10 17077.6753393665 275.2630090498) (10 17107.8450226244 291.4035067873) (10 17119.157239819
305.4298642534))
((0 . "LWPOLYLINE") (100 . "AcDbEntity") (8 . "PLANTS") (62 . 94) (370 . 13) (100 . "AcDbPolyline") (90 . 2) (70 . 0)
(43 . 0.0) (10 17104.07239819 6972.0962669683) (10 17119.157239819 6941.9308823529))
((0 . "LWPOLYLINE") (100 . "AcDbEntity") (8 . "PLANTS") (62 . 94) (370 . 13) (100 . "AcDbPolyline") (90 . 3) (70 . 0)
(43 . 0.0) (10 17115.3846153846 6847.6618778281) (10 17120.203959276 6877.8280542986) (10 17138.0090497738
6900.4524886878))
((0 . "LWPOLYLINE") (100 . "AcDbEntity") (8 . "PLANTS") (62 . 94) (370 . 13) (100 . "AcDbPolyline") (90 . 3) (70 . 0)
(43 . 0.0) (10 17115.3846153846 6847.6618778281) (10 17153.0938914027 6847.8101809955) (10 17164.4061085973
6851.4331447964))
((0 . "LWPOLYLINE") (100 . "AcDbEntity") (8 . "PLANTS") (62 . 94) (370 . 13) (100 . "AcDbPolyline") (90 . 2) (70 . 0)
(43 . 0.0) (10 17119.157239819 6941.9308823529) (10 17138.0090497738 6941.9308823529))
((0 . "LWPOLYLINE") (100 . "AcDbEntity") (8 . "PLANTS") (62 . 94) (370 . 13) (100 . "AcDbPolyline") (90 . 2) (70 . 0)
(43 . 0.0) (10 17138.0090497738 6941.9308823529) (10 17138.0090497738 6900.4524886878))
((0 . "LWPOLYLINE") (100 . "AcDbEntity") (8 . "PLANTS") (62 . 94) (370 . 13) (100 . "AcDbPolyline") (90 . 3) (70 . 0)
(43 . 0.0) (10 17153.0938914027 6960.7840497738) (10 17149.1679864253 6949.4783936652) (10 17138.0090497738
6941.9308823529))
((0 . "LWPOLYLINE") (100 . "AcDbEntity") (8 . "PLANTS") (62 . 94) (370 . 13) (100 . "AcDbPolyline") (90 . 2) (70 . 0)
(43 . 0.0) (10 17156.8608597285 6896.6820135747) (10 17138.0090497738 6900.4524886878))
((0 . "LWPOLYLINE") (100 . "AcDbEntity") (8 . "PLANTS") (62 . 94) (370 . 13) (100 . "AcDbPolyline") (90 . 3) (70 . 0)
(43 . 0.0) (10 17153.0938914027 6960.7840497738) (10 17142.9912895928 6972.0962669683) (10 17145.5486425339
6983.4084841629))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17171.9457013575 7077.6774886878 0.0) (10 17177.2184869895 7049.0610489136 0.0) (10 17147.9686877178
7027.3514903142 0.0) (10 17153.0938914027 6998.4919683258 0.0))
((0 . "LWPOLYLINE") (100 . "AcDbEntity") (8 . "PLANTS") (62 . 94) (370 . 13) (100 . "AcDbPolyline") (90 . 2) (70 . 0)
(43 . 0.0) (10 17153.0938914027 6960.7840497738) (10 17164.4061085973 6960.7840497738))
((0 . "LWPOLYLINE") (100 . "AcDbEntity") (8 . "PLANTS") (62 . 94) (370 . 13) (100 . "AcDbPolyline") (90 . 2) (70 . 0)
(43 . 0.0) (10 17164.4061085973 6851.4331447964) (10 17156.8608597285 6896.6820135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17232.2794117647 6923.0769230769 0.0) (10 17205.0734476187 6936.3958092804 0.0) (10 17175.5984622344
6911.8633101349 0.0) (10 17156.8608597285 6896.6820135747 0.0))
((0 . "LWPOLYLINE") (100 . "AcDbEntity") (8 . "PLANTS") (62 . 94) (370 . 13) (100 . "AcDbPolyline") (90 . 3) (70 . 0)
(43 . 0.0) (10 17209.6549773756 6964.5553167421) (10 17171.95260181 6958.2113122172) (10 17164.4061085973
6960.7840497738))
((0 . "LWPOLYLINE") (100 . "AcDbEntity") (8 . "PLANTS") (62 . 94) (370 . 13) (100 . "AcDbPolyline") (90 . 2) (70 . 0)
(43 . 0.0) (10 17179.4852941176 6990.9502262443) (10 17164.4061085973 6960.7840497738))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17258.6708144796 6855.2036199095 0.0) (10 17230.1636934756 6840.5018280576 0.0) (10 17194.2800531287
6840.2145887369 0.0) (10 17164.4061085973 6851.4331447964 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.300267306)
(40 . 0.3464130094) (40 . 1) (40 . 1) (40 . 1) (40 . 1) (10 17171.9457013575 7077.6774886878 0.0) (10 17179.2357803225
7099.7810389876 0.0) (10 17210.8082816904 7101.3125632489 0.0) (10 17234.0772795629 7057.5336459351 0.0) (10
17179.8023578059 7024.4947896228 0.0) (10 17179.4852941177 6990.9502262444 0.0))
((0 . "LWPOLYLINE") (100 . "AcDbEntity") (8 . "PLANTS") (62 . 94) (370 . 13) (100 . "AcDbPolyline") (90 . 3) (70 . 0)
(43 . 0.0) (10 17262.443438914 6987.1797511312) (10 17273.9033936652 7006.032918552) (10 17304.8745915123
7035.3413744263))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17281.7828862314 7056.1239091791 0.0) (10 17244.1448206512 7038.8969084863 0.0) (10 17225.2023376358
6988.1415095274 0.0) (10 17179.4852941176 6990.9502262443 0.0))
((0 . "LWPOLYLINE") (100 . "AcDbEntity") (8 . "PLANTS") (62 . 94) (370 . 13) (100 . "AcDbPolyline") (90 . 3) (70 . 0)
(43 . 0.0) (10 17217.1945701357 6787.3303167421) (10 17228.5067873303 6777.22239819) (10 17239.8190045249
6776.0180995475))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17217.1945701358 6787.3303167421 0.0) (10 17244.9833147559 6816.5087147057 0.0) (10 17296.3037510467
6793.8839056496 0.0) (10 17330.3167420814 6787.3303167421 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17254.9038461539 6896.6820135747 0.0) (10 17240.4552698557 6892.9879758667 0.0) (10 17228.577472324
6909.6803448722 0.0) (10 17232.2794117647 6923.0769230769 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17285.0678733032 6915.5351809955 0.0) (10 17275.9239332529 6933.9705752491 0.0) (10 17247.556059351
6947.9335462012 0.0) (10 17232.2794117647 6923.0769230769 0.0))
((0 . "LWPOLYLINE") (100 . "AcDbEntity") (8 . "PLANTS") (62 . 94) (370 . 13) (100 . "AcDbPolyline") (90 . 2) (70 . 0)
(43 . 0.0) (10 17262.443438914 6987.1797511312) (10 17236.0463800905 6975.8675339367))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17334.0763542459 3744.3438914027 0.0) (10 17348.6112283675 3771.4352221122 0.0) (10 17327.5888858032
3826.3404534554 0.0) (10 17283.4027583203 3792.9229901466 0.0))
((0 . "LWPOLYLINE") (100 . "AcDbEntity") (8 . "PLANTS") (62 . 94) (370 . 13) (100 . "AcDbPolyline") (90 . 2) (70 . 0)
(43 . 0.0) (10 17509.8223154177 180.9954751131) (10 17648.5487253063 180.9954751131))
((0 . "LWPOLYLINE") (100 . "AcDbEntity") (8 . "PLANTS") (62 . 94) (370 . 13) (100 . "AcDbPolyline") (90 . 3) (70 . 0)
(43 . 0.0) (10 17371.7929864253 3895.1738687783) (10 17349.1685520362 3884.0095022624) (10 17288.0397803352
3886.0343118017))
((0 . "LWPOLYLINE") (100 . "AcDbEntity") (8 . "PLANTS") (62 . 94) (370 . 13) (100 . "AcDbPolyline") (90 . 2) (70 . 0)
(43 . 0.0) (10 17509.0448090596 3012.2375498239) (10 17649.2522175191 3011.9340918284))
((0 . "LWPOLYLINE") (100 . "AcDbEntity") (8 . "PLANTS") (62 . 94) (370 . 13) (100 . "AcDbPolyline") (90 . 2) (70 . 0)
(43 . 0.0) (10 17254.9038461538 6896.6820135747) (10 17258.6708144796 6855.2036199095))
((0 . "LWPOLYLINE") (100 . "AcDbEntity") (8 . "PLANTS") (62 . 94) (370 . 13) (100 . "AcDbPolyline") (90 . 2) (70 . 0)
(43 . 0.0) (10 17254.9038461538 6896.6820135747) (10 17285.0678733032 6915.5351809955))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17285.1432680419 1052.1869885725 0.0) (10 17296.5854829402 1053.2651588451 0.0) (10 17318.2022260115
1048.165722506 0.0) (10 17322.7771493213 1063.3484162896 0.0))
((0 . "LWPOLYLINE") (100 . "AcDbEntity") (8 . "PLANTS") (62 . 94) (370 . 13) (100 . "AcDbPolyline") (90 . 3) (70 . 0)
(43 . 0.0) (10 17258.6708144796 6855.2036199095) (10 17277.528280543 6847.8101809955) (10 17303.9196832579
6847.6618778281))
((0 . "LWPOLYLINE") (100 . "AcDbEntity") (8 . "PLANTS") (62 . 94) (370 . 13) (100 . "AcDbPolyline") (90 . 2) (70 . 0)
(43 . 0.0) (10 17262.443438914 6987.1797511312) (10 17281.2952488688 6972.0962669683))
((0 . "LWPOLYLINE") (100 . "AcDbEntity") (8 . "PLANTS") (62 . 94) (370 . 13) (100 . "AcDbPolyline") (90 . 3) (70 . 0)
(43 . 0.0) (10 17379.3382352941 935.1442307692) (10 17330.3167420814 931.3716063348) (10 17299.2366980019
933.200812141))
((0 . "LWPOLYLINE") (100 . "AcDbEntity") (8 . "PLANTS") (62 . 94) (370 . 13) (100 . "AcDbPolyline") (90 . 3) (70 . 0)
(43 . 0.0) (10 17330.3167420814 6787.3303167421) (10 17317.8087104072 6749.6297511312) (10 17289.0665021342
6730.7692307692))
((0 . "LWPOLYLINE") (100 . "AcDbEntity") (8 . "PLANTS") (62 . 94) (370 . 13) (100 . "AcDbPolyline") (90 . 2) (70 . 0)
(43 . 0.0) (10 17285.0678733032 6915.5351809955) (10 17307.6923076923 6926.84739819))
((0 . "LWPOLYLINE") (100 . "AcDbEntity") (8 . "PLANTS") (62 . 94) (370 . 13) (100 . "AcDbPolyline") (90 . 3) (70 . 0)
(43 . 0.0) (10 17315.2319004525 972.850678733) (10 17307.6854072398 979.1944570136) (10 17288.8404977376
984.1628959276))
((0 . "LWPOLYLINE") (100 . "AcDbEntity") (8 . "PLANTS") (62 . 94) (370 . 13) (100 . "AcDbPolyline") (90 . 2) (70 . 0)
(43 . 0.0) (10 17375.5656108597 6847.6618778281) (10 17303.9196832579 6847.6618778281))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6012299175) (40
. 1) (40 . 1) (40 . 1) (40 . 1) (10 17360.4807692308 6900.4524886877 0.0) (10 17352.0701874922 6886.1598638871 0.0) (10
17310.051204181 6888.1294866681 0.0) (10 17297.1672448514 6865.5196757576 0.0) (10 17303.9196832579 6847.661877828 0.0))
((0 . "LWPOLYLINE") (100 . "AcDbEntity") (8 . "PLANTS") (62 . 94) (370 . 13) (100 . "AcDbPolyline") (90 . 3) (70 . 0)
(43 . 0.0) (10 17330.3167420814 6930.6186651584) (10 17319.0045248869 6923.2383484163) (10 17307.6923076923
6926.84739819))
((0 . "LWPOLYLINE") (100 . "AcDbEntity") (8 . "PLANTS") (62 . 94) (370 . 13) (100 . "AcDbPolyline") (90 . 2) (70 . 0)
(43 . 0.0) (10 17322.7771493213 6941.9308823529) (10 17307.6923076923 6926.84739819))
((0 . "LWPOLYLINE") (100 . "AcDbEntity") (8 . "PLANTS") (62 . 94) (370 . 13) (100 . "AcDbPolyline") (90 . 2) (70 . 0)
(43 . 0.0) (10 17325.2893665158 3960.5334841629) (10 17330.3167420814 3963.0471719457))
((0 . "LWPOLYLINE") (100 . "AcDbEntity") (8 . "PLANTS") (62 . 94) (370 . 13) (100 . "AcDbPolyline") (90 . 3) (70 . 0)
(43 . 0.0) (10 17318.9792546435 1119.8589617757) (10 17326.3977375566 1104.8274886878) (10 17322.7771493213
1063.3484162896))
((0 . "LWPOLYLINE") (100 . "AcDbEntity") (8 . "PLANTS") (62 . 94) (370 . 13) (100 . "AcDbPolyline") (90 . 3) (70 . 0)
(43 . 0.0) (10 17330.3167420814 6930.6186651584) (10 17330.3167420814 6938.1596153846) (10 17322.7771493213
6941.9308823529))
((0 . "LWPOLYLINE") (100 . "AcDbEntity") (8 . "PLANTS") (62 . 94) (370 . 13) (100 . "AcDbPolyline") (90 . 2) (70 . 0)
(43 . 0.0) (10 17326.5441176471 6953.2430995475) (10 17322.7771493213 6941.9308823529))
((0 . "LWPOLYLINE") (100 . "AcDbEntity") (8 . "PLANTS") (62 . 94) (370 . 13) (100 . "AcDbPolyline") (90 . 3) (70 . 0)
(43 . 0.0) (10 17379.3382352941 1070.8908371041) (10 17364.2533936652 1063.4968325792) (10 17322.7771493213
1063.3484162896))
((0 . "LWPOLYLINE") (100 . "AcDbEntity") (8 . "PLANTS") (62 . 94) (370 . 13) (100 . "AcDbPolyline") (90 . 2) (70 . 0)
(43 . 0.0) (10 17368.0260180995 1131.221719457) (10 17326.5454702148 1134.9913929183))
((0 . "LWPOLYLINE") (100 . "AcDbEntity") (8 . "PLANTS") (62 . 94) (370 . 13) (100 . "AcDbPolyline") (90 . 3) (70 . 0)
(43 . 0.0) (10 17375.5656108597 6923.0769230769) (10 17356.713800905 6930.470361991) (10 17330.3167420814
6930.6186651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17330.3167420814 6787.3303167421 0.0) (10 17362.4579733078 6784.5189034555 0.0) (10 17388.0446771296
6817.6167868972 0.0) (10 17375.5656108597 6847.6618778281 0.0))
((0 . "LWPOLYLINE") (100 . "AcDbEntity") (8 . "PLANTS") (62 . 94) (370 . 13) (100 . "AcDbPolyline") (90 . 3) (70 . 0)
(43 . 0.0) (10 17360.4807692308 3925.3393665158) (10 17338.0124434389 3936.6578054299) (10 17330.3167420814
3963.0471719457))
((0 . "LWPOLYLINE") (100 . "AcDbEntity") (8 . "PLANTS") (62 . 94) (370 . 13) (100 . "AcDbPolyline") (90 . 2) (70 . 0)
(43 . 0.0) (10 17332.8326175821 3975.6199862954) (10 17330.3167420814 3963.0471719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17560.3337104072 3740.5727375566 0.0) (10 17503.1215597349 3756.015939973 0.0) (10 17446.4503365641
3719.1198793841 0.0) (10 17388.5080311745 3740.5751665168 0.0))
((0 . "LWPOLYLINE") (100 . "AcDbEntity") (8 . "PLANTS") (62 . 94) (370 . 13) (100 . "AcDbPolyline") (90 . 2) (70 . 0)
(43 . 0.0) (10 17358.9876672717 1199.875787032) (10 17368.0260180995 1195.3252262443))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17354.0867454938 4018.1282421189 0.0) (10 17369.9562708419 4013.6879987753 0.0) (10 17384.2322906708
3999.6488832245 0.0) (10 17383.1052036199 3981.9004524887 0.0))
((0 . "LWPOLYLINE") (100 . "AcDbEntity") (8 . "PLANTS") (62 . 94) (370 . 13) (100 . "AcDbPolyline") (90 . 2) (70 . 0)
(43 . 0.0) (10 17371.7929864253 3895.1738687783) (10 17360.4807692308 3925.3393665158))
((0 . "LWPOLYLINE") (100 . "AcDbEntity") (8 . "PLANTS") (62 . 94) (370 . 13) (100 . "AcDbPolyline") (90 . 2) (70 . 0)
(43 . 0.0) (10 17375.5656108597 3944.1926470588) (10 17360.4807692308 3925.3393665158))
((0 . "LWPOLYLINE") (100 . "AcDbEntity") (8 . "PLANTS") (62 . 94) (370 . 13) (100 . "AcDbPolyline") (90 . 2) (70 . 0)
(43 . 0.0) (10 17368.0260180995 1195.3252262443) (10 17379.3382352941 1146.3037330317))
((0 . "LWPOLYLINE") (100 . "AcDbEntity") (8 . "PLANTS") (62 . 94) (370 . 13) (100 . "AcDbPolyline") (90 . 3) (70 . 0)
(43 . 0.0) (10 17368.0260180995 1195.3252262443) (10 17379.3382352941 1201.8091628959) (10 17398.1900452489
1202.8648190045))
((0 . "LWPOLYLINE") (100 . "AcDbEntity") (8 . "PLANTS") (62 . 94) (370 . 13) (100 . "AcDbPolyline") (90 . 3) (70 . 0)
(43 . 0.0) (10 17368.0260180995 1131.221719457) (10 17372.9985294118 1101.0548642534) (10 17383.1052036199
1089.7426470588))
((0 . "LWPOLYLINE") (100 . "AcDbEntity") (8 . "PLANTS") (62 . 94) (370 . 13) (100 . "AcDbPolyline") (90 . 2) (70 . 0)
(43 . 0.0) (10 17368.0260180995 1131.221719457) (10 17379.3382352941 1146.3037330317))
((0 . "LWPOLYLINE") (100 . "AcDbEntity") (8 . "PLANTS") (62 . 94) (370 . 13) (100 . "AcDbPolyline") (90 . 2) (70 . 0)
(43 . 0.0) (10 17371.7929864253 3895.1738687783) (10 17386.8778280543 3895.1738687783))
((0 . "LWPOLYLINE") (100 . "AcDbEntity") (8 . "PLANTS") (62 . 94) (370 . 13) (100 . "AcDbPolyline") (90 . 2) (70 . 0)
(43 . 0.0) (10 17375.5656108597 6923.0769230769) (10 17383.1052036199 6923.0769230769))
((0 . "LWPOLYLINE") (100 . "AcDbEntity") (8 . "PLANTS") (62 . 94) (370 . 13) (100 . "AcDbPolyline") (90 . 3) (70 . 0)
(43 . 0.0) (10 17375.5656108597 6923.0769230769) (10 17379.3382352941 6915.5351809955) (10 17383.1052036199
6923.0769230769))
((0 . "LWPOLYLINE") (100 . "AcDbEntity") (8 . "PLANTS") (62 . 94) (370 . 13) (100 . "AcDbPolyline") (90 . 3) (70 . 0)
(43 . 0.0) (10 17390.6504524887 6870.2863122172) (10 17389.4449095023 6862.7384615385) (10 17375.5656108597
6847.6618778281))
((0 . "LWPOLYLINE") (100 . "AcDbEntity") (8 . "PLANTS") (62 . 94) (370 . 13) (100 . "AcDbPolyline") (90 . 2) (70 . 0)
(43 . 0.0) (10 17375.5656108597 3944.1926470588) (10 17401.9626696833 3944.1926470588))
((0 . "LWPOLYLINE") (100 . "AcDbEntity") (8 . "PLANTS") (62 . 94) (370 . 13) (100 . "AcDbPolyline") (90 . 3) (70 . 0)
(43 . 0.0) (10 17375.5656108597 3944.1926470588) (10 17375.7133484163 3966.817081448) (10 17383.1052036199
3981.9004524887))
((0 . "LWPOLYLINE") (100 . "AcDbEntity") (8 . "PLANTS") (62 . 94) (370 . 13) (100 . "AcDbPolyline") (90 . 3) (70 . 0)
(43 . 0.0) (10 17405.7296380091 4034.6903846154) (10 17383.2557692308 4042.3866515837) (10 17382.603542423
4043.5588020054))
((0 . "LWPOLYLINE") (100 . "AcDbEntity") (8 . "PLANTS") (62 . 94) (370 . 13) (100 . "AcDbPolyline") (90 . 3) (70 . 0)
(43 . 0.0) (10 17417.0418552036 1134.9915158371) (10 17409.495361991 1141.3359728507) (10 17379.3382352941
1146.3037330317))
((0 . "LWPOLYLINE") (100 . "AcDbEntity") (8 . "PLANTS") (62 . 94) (370 . 13) (100 . "AcDbPolyline") (90 . 3) (70 . 0)
(43 . 0.0) (10 17379.3382352941 1070.8908371041) (10 17401.9626696833 1059.7263574661) (10 17443.4389140271
1059.5786199095))
((0 . "LWPOLYLINE") (100 . "AcDbEntity") (8 . "PLANTS") (62 . 94) (370 . 13) (100 . "AcDbPolyline") (90 . 2) (70 . 0)
(43 . 0.0) (10 17379.3382352941 1070.8908371041) (10 17383.1052036199 1089.7426470588))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4436363186) (40
. 1) (40 . 1) (40 . 1) (40 . 1) (10 17481.1481900453 937.0277149322 0.0) (10 17464.5766358276 940.7671001832 0.0) (10
17431.3765668691 910.7644869818 0.0) (10 17402.8092701287 953.1724154105 0.0) (10 17379.3382352941 935.1442307692 0.0))
((0 . "LWPOLYLINE") (100 . "AcDbEntity") (8 . "PLANTS") (62 . 94) (370 . 13) (100 . "AcDbPolyline") (90 . 3) (70 . 0)
(43 . 0.0) (10 17394.4174208145 976.6204751131) (10 17380.5409502262 961.5384615385) (10 17379.3382352941
935.1442307692))
((0 . "LWPOLYLINE") (100 . "AcDbEntity") (8 . "PLANTS") (62 . 94) (370 . 13) (100 . "AcDbPolyline") (90 . 2) (70 . 0)
(43 . 0.0) (10 17409.5022624434 6919.3064479638) (10 17383.1052036199 6923.0769230769))
((0 . "LWPOLYLINE") (100 . "AcDbEntity") (8 . "PLANTS") (62 . 94) (370 . 13) (100 . "AcDbPolyline") (90 . 3) (70 . 0)
(43 . 0.0) (10 17409.5022624434 3974.3593891403) (10 17401.9542986425 3981.7458144796) (10 17383.1052036199
3981.9004524887))
((0 . "LWPOLYLINE") (100 . "AcDbEntity") (8 . "PLANTS") (62 . 94) (370 . 13) (100 . "AcDbPolyline") (90 . 2) (70 . 0)
(43 . 0.0) (10 17417.0418552036 1112.367081448) (10 17383.1052036199 1089.7426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17386.8778280543 3895.1738687782 0.0) (10 17402.4741813703 3879.4556361731 0.0) (10 17435.4557138928
3879.1500584152 0.0) (10 17450.9785067873 3895.1738687783 0.0))
((0 . "LWPOLYLINE") (100 . "AcDbEntity") (8 . "PLANTS") (62 . 94) (370 . 13) (100 . "AcDbPolyline") (90 . 2) (70 . 0)
(43 . 0.0) (10 17386.8778280543 3895.1738687783) (10 17401.9626696833 3929.110520362))
((0 . "LWPOLYLINE") (100 . "AcDbEntity") (8 . "PLANTS") (62 . 94) (370 . 13) (100 . "AcDbPolyline") (90 . 2) (70 . 0)
(43 . 0.0) (10 17394.4174208145 976.6204751131) (10 17405.7296380091 972.850678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17394.4174208145 976.6204751131 0.0) (10 17397.476961043 997.2993668548 0.0) (10 17417.023963384
1028.5298873607 0.0) (10 17443.4389140271 1010.5571266968 0.0))
((0 . "LWPOLYLINE") (100 . "AcDbEntity") (8 . "PLANTS") (62 . 94) (370 . 13) (100 . "AcDbPolyline") (90 . 2) (70 . 0)
(43 . 0.0) (10 17405.7296380091 4034.6903846154) (10 17407.9130121372 4050.5892102593))
((0 . "LWPOLYLINE") (100 . "AcDbEntity") (8 . "PLANTS") (62 . 94) (370 . 13) (100 . "AcDbPolyline") (90 . 3) (70 . 0)
(43 . 0.0) (10 17420.814479638 1187.7828054299) (10 17409.5091628959 1188.9876696833) (10 17398.1900452489
1202.8648190045))
((0 . "LWPOLYLINE") (100 . "AcDbEntity") (8 . "PLANTS") (62 . 94) (370 . 13) (100 . "AcDbPolyline") (90 . 2) (70 . 0)
(43 . 0.0) (10 17408.0442415823 1222.5713642404) (10 17398.1900452489 1202.8648190045))
((0 . "LWPOLYLINE") (100 . "AcDbEntity") (8 . "PLANTS") (62 . 94) (370 . 13) (100 . "AcDbPolyline") (90 . 2) (70 . 0)
(43 . 0.0) (10 17401.9626696833 3929.110520362) (10 17401.9626696833 3944.1926470588))
((0 . "LWPOLYLINE") (100 . "AcDbEntity") (8 . "PLANTS") (62 . 94) (370 . 13) (100 . "AcDbPolyline") (90 . 2) (70 . 0)
(43 . 0.0) (10 17409.5022624434 3974.3593891403) (10 17401.9626696833 3944.1926470588))
((0 . "LWPOLYLINE") (100 . "AcDbEntity") (8 . "PLANTS") (62 . 94) (370 . 13) (100 . "AcDbPolyline") (90 . 2) (70 . 0)
(43 . 0.0) (10 17401.9626696833 3929.110520362) (10 17443.4389140271 3929.110520362))
((0 . "LWPOLYLINE") (100 . "AcDbEntity") (8 . "PLANTS") (62 . 94) (370 . 13) (100 . "AcDbPolyline") (90 . 2) (70 . 0)
(43 . 0.0) (10 17405.7296380091 4034.6903846154) (10 17409.5022624434 4012.0659502262))
((0 . "LWPOLYLINE") (100 . "AcDbEntity") (8 . "PLANTS") (62 . 94) (370 . 13) (100 . "AcDbPolyline") (90 . 3) (70 . 0)
(43 . 0.0) (10 17409.5022624434 3974.3593891403) (10 17420.814479638 3974.3593891403) (10 17424.5871040724
3978.1292986425))
((0 . "LWPOLYLINE") (100 . "AcDbEntity") (8 . "PLANTS") (62 . 94) (370 . 13) (100 . "AcDbPolyline") (90 . 2) (70 . 0)
(43 . 0.0) (10 17413.2748868778 4000.7537330317) (10 17424.5871040724 3978.1292986425))
((0 . "LWPOLYLINE") (100 . "AcDbEntity") (8 . "PLANTS") (62 . 94) (370 . 13) (100 . "AcDbPolyline") (90 . 2) (70 . 0)
(43 . 0.0) (10 17417.0418552036 1112.367081448) (10 17417.0418552036 1134.9915158371))
((0 . "LWPOLYLINE") (100 . "AcDbEntity") (8 . "PLANTS") (62 . 94) (370 . 13) (100 . "AcDbPolyline") (90 . 2) (70 . 0)
(43 . 0.0) (10 17417.0418552036 1134.9915158371) (10 17439.6662895928 1146.3037330317))
((0 . "LWPOLYLINE") (100 . "AcDbEntity") (8 . "PLANTS") (62 . 94) (370 . 13) (100 . "AcDbPolyline") (90 . 3) (70 . 0)
(43 . 0.0) (10 17417.0418552036 1112.367081448) (10 17435.899321267 1111.3114253394) (10 17454.7511312217
1101.0548642534))
((0 . "LWPOLYLINE") (100 . "AcDbEntity") (8 . "PLANTS") (62 . 94) (370 . 13) (100 . "AcDbPolyline") (90 . 2) (70 . 0)
(43 . 0.0) (10 17439.6662895928 1165.1583710407) (10 17420.814479638 1187.7828054299))
((0 . "LWPOLYLINE") (100 . "AcDbEntity") (8 . "PLANTS") (62 . 94) (370 . 13) (100 . "AcDbPolyline") (90 . 2) (70 . 0)
(43 . 0.0) (10 17450.9785067873 1229.2618778281) (10 17420.814479638 1187.7828054299))
((0 . "LWPOLYLINE") (100 . "AcDbEntity") (8 . "PLANTS") (62 . 94) (370 . 13) (100 . "AcDbPolyline") (90 . 2) (70 . 0)
(43 . 0.0) (10 17450.9785067873 3981.9004524887) (10 17424.5871040724 3978.1292986425))
((0 . "LWPOLYLINE") (100 . "AcDbEntity") (8 . "PLANTS") (62 . 94) (370 . 13) (100 . "AcDbPolyline") (90 . 2) (70 . 0)
(43 . 0.0) (10 17439.6662895928 1165.1583710407) (10 17439.6662895928 1146.3037330317))
((0 . "LWPOLYLINE") (100 . "AcDbEntity") (8 . "PLANTS") (62 . 94) (370 . 13) (100 . "AcDbPolyline") (90 . 3) (70 . 0)
(43 . 0.0) (10 17492.4604072398 1202.8648190045) (10 17469.8400452489 1194.1265837104) (10 17439.6662895928
1165.1583710407))
((0 . "LWPOLYLINE") (100 . "AcDbEntity") (8 . "PLANTS") (62 . 94) (370 . 13) (100 . "AcDbPolyline") (90 . 3) (70 . 0)
(43 . 0.0) (10 17477.3755656109 1146.3037330317) (10 17462.2907239819 1142.5339366516) (10 17439.6662895928
1146.3037330317))
((0 . "LWPOLYLINE") (100 . "AcDbEntity") (8 . "PLANTS") (62 . 94) (370 . 13) (100 . "AcDbPolyline") (90 . 3) (70 . 0)
(43 . 0.0) (10 17450.9785067873 3895.1738687783) (10 17443.5921945701 3910.2559954751) (10 17443.4389140271
3929.110520362))
((0 . "LWPOLYLINE") (100 . "AcDbEntity") (8 . "PLANTS") (62 . 94) (370 . 13) (100 . "AcDbPolyline") (90 . 2) (70 . 0)
(43 . 0.0) (10 17458.5237556561 3944.1926470588) (10 17443.4389140271 3929.110520362))
((0 . "LWPOLYLINE") (100 . "AcDbEntity") (8 . "PLANTS") (62 . 94) (370 . 13) (100 . "AcDbPolyline") (90 . 2) (70 . 0)
(43 . 0.0) (10 17448.034062991 1233.6796479651) (10 17450.9785067873 1229.2618778281))
((0 . "LWPOLYLINE") (100 . "AcDbEntity") (8 . "PLANTS") (62 . 94) (370 . 13) (100 . "AcDbPolyline") (90 . 2) (70 . 0)
(43 . 0.0) (10 17450.9785067873 1036.9541855204) (10 17443.4389140271 1059.5786199095))
((0 . "LWPOLYLINE") (100 . "AcDbEntity") (8 . "PLANTS") (62 . 94) (370 . 13) (100 . "AcDbPolyline") (90 . 2) (70 . 0)
(43 . 0.0) (10 17454.7511312217 1074.6606334842) (10 17443.4389140271 1059.5786199095))
((0 . "LWPOLYLINE") (100 . "AcDbEntity") (8 . "PLANTS") (62 . 94) (370 . 13) (100 . "AcDbPolyline") (90 . 3) (70 . 0)
(43 . 0.0) (10 17481.1481900452 991.7053167421) (10 17454.7511312217 998.3507918552) (10 17443.4389140271
1010.5571266968))
((0 . "LWPOLYLINE") (100 . "AcDbEntity") (8 . "PLANTS") (62 . 94) (370 . 13) (100 . "AcDbPolyline") (90 . 2) (70 . 0)
(43 . 0.0) (10 17450.9785067873 1036.9541855204) (10 17443.4389140271 1010.5571266968))
((0 . "LWPOLYLINE") (100 . "AcDbEntity") (8 . "PLANTS") (62 . 94) (370 . 13) (100 . "AcDbPolyline") (90 . 3) (70 . 0)
(43 . 0.0) (10 17453.8309511838 4063.3441933278) (10 17458.3800904977 4060.9313348416) (10 17488.6877828054
4019.6082579186))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17446.6894532947 4061.3604439142 0.0) (10 17420.8582434535 4048.4651371283 0.0) (10 17433.1721740874
4004.7282705116 0.0) (10 17450.9785067873 3989.4415158371 0.0))
((0 . "LWPOLYLINE") (100 . "AcDbEntity") (8 . "PLANTS") (62 . 94) (370 . 13) (100 . "AcDbPolyline") (90 . 2) (70 . 0)
(43 . 0.0) (10 17450.9785067873 3981.9004524887) (10 17450.9785067873 3989.4415158371))
((0 . "LWPOLYLINE") (100 . "AcDbEntity") (8 . "PLANTS") (62 . 94) (370 . 13) (100 . "AcDbPolyline") (90 . 3) (70 . 0)
(43 . 0.0) (10 17450.9785067873 3989.4415158371) (10 17480.9976244344 4004.6729638009) (10 17488.6877828054
4019.6082579186))
((0 . "LWPOLYLINE") (100 . "AcDbEntity") (8 . "PLANTS") (62 . 94) (370 . 13) (100 . "AcDbPolyline") (90 . 3) (70 . 0)
(43 . 0.0) (10 17450.9785067873 3981.9004524887) (10 17457.4728506787 3966.817081448) (10 17458.5237556561
3951.7349547511))
((0 . "LWPOLYLINE") (100 . "AcDbEntity") (8 . "PLANTS") (62 . 94) (370 . 13) (100 . "AcDbPolyline") (90 . 2) (70 . 0)
(43 . 0.0) (10 17450.9785067873 3895.1738687783) (10 17466.0633484163 3895.1738687783))
((0 . "LWPOLYLINE") (100 . "AcDbEntity") (8 . "PLANTS") (62 . 94) (370 . 13) (100 . "AcDbPolyline") (90 . 3) (70 . 0)
(43 . 0.0) (10 17450.9785067873 1229.2618778281) (10 17466.129638009 1234.3035067873) (10 17473.5521145449
1240.7679956189))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17488.6877828054 1003.0175339366 0.0) (10 17469.5228529283 1014.8467846383 0.0) (10 17492.5189987293
1057.6731082719 0.0) (10 17450.9785067873 1036.9541855204 0.0))
((0 . "LWPOLYLINE") (100 . "AcDbEntity") (8 . "PLANTS") (62 . 94) (370 . 13) (100 . "AcDbPolyline") (90 . 3) (70 . 0)
(43 . 0.0) (10 17530.1640271493 1108.5972850679) (10 17507.5395927602 1097.4334841629) (10 17454.7511312217
1101.0548642534))
((0 . "LWPOLYLINE") (100 . "AcDbEntity") (8 . "PLANTS") (62 . 94) (370 . 13) (100 . "AcDbPolyline") (90 . 2) (70 . 0)
(43 . 0.0) (10 17454.7511312217 1101.0548642534) (10 17454.7511312217 1074.6606334842))
((0 . "LWPOLYLINE") (100 . "AcDbEntity") (8 . "PLANTS") (62 . 94) (370 . 13) (100 . "AcDbPolyline") (90 . 3) (70 . 0)
(43 . 0.0) (10 17454.7511312217 1074.6606334842) (10 17469.8359728507 1069.6921945701) (10 17481.1481900452
1059.5786199095))
((0 . "LWPOLYLINE") (100 . "AcDbEntity") (8 . "PLANTS") (62 . 94) (370 . 13) (100 . "AcDbPolyline") (90 . 2) (70 . 0)
(43 . 0.0) (10 17458.5237556561 3944.1926470588) (10 17458.5237556561 3951.7349547511))
((0 . "LWPOLYLINE") (100 . "AcDbEntity") (8 . "PLANTS") (62 . 94) (370 . 13) (100 . "AcDbPolyline") (90 . 3) (70 . 0)
(43 . 0.0) (10 17522.6244343891 3944.1926470588) (10 17500 3955.3570135747) (10 17458.5237556561 3951.7349547511))
((0 . "LWPOLYLINE") (100 . "AcDbEntity") (8 . "PLANTS") (62 . 94) (370 . 13) (100 . "AcDbPolyline") (90 . 3) (70 . 0)
(43 . 0.0) (10 17458.5237556561 3944.1926470588) (10 17468.6304298643 3936.645361991) (10 17473.6029411765
3917.7983031674))
((0 . "LWPOLYLINE") (100 . "AcDbEntity") (8 . "PLANTS") (62 . 94) (370 . 13) (100 . "AcDbPolyline") (90 . 2) (70 . 0)
(43 . 0.0) (10 17462.2907239819 663.6510180995) (10 17481.1481900452 667.4208144796))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17466.0633484163 3895.1738687782 0.0) (10 17493.9616050971 3873.8183638735 0.0) (10 17547.9812198318
3879.7887154895 0.0) (10 17571.6459276019 3902.7149321265 0.0))
((0 . "LWPOLYLINE") (100 . "AcDbEntity") (8 . "PLANTS") (62 . 94) (370 . 13) (100 . "AcDbPolyline") (90 . 2) (70 . 0)
(43 . 0.0) (10 17466.0633484163 3895.1738687783) (10 17473.6029411765 3917.7983031674))
((0 . "LWPOLYLINE") (100 . "AcDbEntity") (8 . "PLANTS") (62 . 94) (370 . 13) (100 . "AcDbPolyline") (90 . 2) (70 . 0)
(43 . 0.0) (10 17466.0633484163 614.6295248869) (10 17484.915158371 618.4021493213))
((0 . "LWPOLYLINE") (100 . "AcDbEntity") (8 . "PLANTS") (62 . 94) (370 . 13) (100 . "AcDbPolyline") (90 . 2) (70 . 0)
(43 . 0.0) (10 17496.2273755656 3921.5682126697) (10 17473.6029411765 3917.7983031674))
((0 . "LWPOLYLINE") (100 . "AcDbEntity") (8 . "PLANTS") (62 . 94) (370 . 13) (100 . "AcDbPolyline") (90 . 3) (70 . 0)
(43 . 0.0) (10 17492.4604072398 1202.8648190045) (10 17487.6383484163 1221.7194570136) (10 17476.0717391713
1241.4678913485))
((0 . "LWPOLYLINE") (100 . "AcDbEntity") (8 . "PLANTS") (62 . 94) (370 . 13) (100 . "AcDbPolyline") (90 . 3) (70 . 0)
(43 . 0.0) (10 17477.3755656109 1146.3037330317) (10 17481.1481900452 1153.8461538462) (10 17486.8042986425
1148.1900452489))
((0 . "LWPOLYLINE") (100 . "AcDbEntity") (8 . "PLANTS") (62 . 94) (370 . 13) (100 . "AcDbPolyline") (90 . 2) (70 . 0)
(43 . 0.0) (10 17477.3755656109 1146.3037330317) (10 17486.8042986425 1148.1900452489))
((0 . "LWPOLYLINE") (100 . "AcDbEntity") (8 . "PLANTS") (62 . 94) (370 . 13) (100 . "AcDbPolyline") (90 . 2) (70 . 0)
(43 . 0.0) (10 17481.1481900452 937.0277149321) (10 17481.1481900452 991.7053167421))
((0 . "LWPOLYLINE") (100 . "AcDbEntity") (8 . "PLANTS") (62 . 94) (370 . 13) (100 . "AcDbPolyline") (90 . 2) (70 . 0)
(43 . 0.0) (10 17488.6877828054 1003.0175339367) (10 17481.1481900452 991.7053167421))
((0 . "LWPOLYLINE") (100 . "AcDbEntity") (8 . "PLANTS") (62 . 94) (370 . 13) (100 . "AcDbPolyline") (90 . 3) (70 . 0)
(43 . 0.0) (10 17481.1481900452 937.0277149321) (10 17481.2945701357 886.1227375566) (10 17484.915158371 874.810520362))
((0 . "LWPOLYLINE") (100 . "AcDbEntity") (8 . "PLANTS") (62 . 94) (370 . 13) (100 . "AcDbPolyline") (90 . 2) (70 . 0)
(43 . 0.0) (10 17481.1481900452 937.0277149321) (10 17526.3970588235 946.4564479638))
((0 . "LWPOLYLINE") (100 . "AcDbEntity") (8 . "PLANTS") (62 . 94) (370 . 13) (100 . "AcDbPolyline") (90 . 2) (70 . 0)
(43 . 0.0) (10 17488.6877828054 663.6510180995) (10 17481.1481900452 667.4208144796))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17484.915158371 874.810520362 0.0) (10 17476.738791723 807.0273473929 0.0) (10 17503.0765974796
734.5676287765 0.0) (10 17481.1481900452 667.4208144796 0.0))
((0 . "LWPOLYLINE") (100 . "AcDbEntity") (8 . "PLANTS") (62 . 94) (370 . 13) (100 . "AcDbPolyline") (90 . 2) (70 . 0)
(43 . 0.0) (10 17484.915158371 874.810520362) (10 17515.084841629 882.3529411765))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3115151549) (40
. 1) (40 . 1) (40 . 1) (40 . 1) (10 17484.915158371 618.4021493213 0.0) (10 17465.2339300327 567.0249143575 0.0) (10
17478.3928719586 452.6747857254 0.0) (10 17658.9045184994 507.4217292966 0.0) (10 17729.0800587757 511.1739423377 0.0))
((0 . "LWPOLYLINE") (100 . "AcDbEntity") (8 . "PLANTS") (62 . 94) (370 . 13) (100 . "AcDbPolyline") (90 . 3) (70 . 0)
(43 . 0.0) (10 17484.915158371 618.4021493213) (10 17488.5400452489 629.7143665158) (10 17488.6877828054
663.6510180995))
((0 . "LWPOLYLINE") (100 . "AcDbEntity") (8 . "PLANTS") (62 . 94) (370 . 13) (100 . "AcDbPolyline") (90 . 2) (70 . 0)
(43 . 0.0) (10 17488.6877828054 1131.221719457) (10 17486.8042986425 1148.1900452489))
((0 . "LWPOLYLINE") (100 . "AcDbEntity") (8 . "PLANTS") (62 . 94) (370 . 13) (100 . "AcDbPolyline") (90 . 2) (70 . 0)
(43 . 0.0) (10 17500 1153.8461538462) (10 17486.8042986425 1148.1900452489))
((0 . "LWPOLYLINE") (100 . "AcDbEntity") (8 . "PLANTS") (62 . 94) (370 . 13) (100 . "AcDbPolyline") (90 . 3) (70 . 0)
(43 . 0.0) (10 17511.3122171946 4027.149321267) (10 17503.7642533937 4020.8055429864) (10 17488.6877828054
4019.6082579186))
((0 . "LWPOLYLINE") (100 . "AcDbEntity") (8 . "PLANTS") (62 . 94) (370 . 13) (100 . "AcDbPolyline") (90 . 3) (70 . 0)
(43 . 0.0) (10 17488.6877828054 1003.0175339367) (10 17511.3122171946 1004.0731900452) (10 17537.7092760181
1021.8693438914))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5023585303)
(40 . 0.6448918421) (40 . 1) (40 . 1) (40 . 1) (40 . 1) (10 17488.6877828054 663.6510180995 0.0) (10 17514.7999150701
655.7345067698 0.0) (10 17520.8618971691 685.0393271889 0.0) (10 17549.4551151796 707.1315465005 0.0) (10
17553.6261130289 726.1076565751 0.0) (10 17564.100678733 735.2941176471 0.0))
((0 . "LWPOLYLINE") (100 . "AcDbEntity") (8 . "PLANTS") (62 . 94) (370 . 13) (100 . "AcDbPolyline") (90 . 3) (70 . 0)
(43 . 0.0) (10 17492.4604072398 1202.8648190045) (10 17502.567081448 1191.55260181) (10 17503.7726244344
1180.2403846154))
((0 . "LWPOLYLINE") (100 . "AcDbEntity") (8 . "PLANTS") (62 . 94) (370 . 13) (100 . "AcDbPolyline") (90 . 2) (70 . 0)
(43 . 0.0) (10 17496.2273755656 1052.036199095) (10 17537.7092760181 1055.8059954751))
((0 . "LWPOLYLINE") (100 . "AcDbEntity") (8 . "PLANTS") (62 . 94) (370 . 13) (100 . "AcDbPolyline") (90 . 3) (70 . 0)
(43 . 0.0) (10 17530.1640271493 1108.5972850679) (10 17521.4202488688 1131.221719457) (10 17500 1153.8461538462))
((0 . "LWPOLYLINE") (100 . "AcDbEntity") (8 . "PLANTS") (62 . 94) (370 . 13) (100 . "AcDbPolyline") (90 . 2) (70 . 0)
(43 . 0.0) (10 17500 1153.8461538462) (10 17503.7726244344 1180.2403846154))
((0 . "LWPOLYLINE") (100 . "AcDbEntity") (8 . "PLANTS") (62 . 94) (370 . 13) (100 . "AcDbPolyline") (90 . 2) (70 . 0)
(43 . 0.0) (10 17549.0214932127 1165.1583710407) (10 17503.7726244344 1180.2403846154))
((0 . "LWPOLYLINE") (100 . "AcDbEntity") (8 . "PLANTS") (62 . 94) (370 . 13) (100 . "AcDbPolyline") (90 . 3) (70 . 0)
(43 . 0.0) (10 17533.9366515837 4038.4615384615) (10 17525.3392533937 4072.3981900452) (10 17518.6743624173
4081.3562520038))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17511.3122171946 4027.149321267 0.0) (10 17494.6136522457 4037.6076794259 0.0) (10 17495.177234184
4058.6914782354 0.0) (10 17497.0557778969 4075.351089637 0.0))
((0 . "LWPOLYLINE") (100 . "AcDbEntity") (8 . "PLANTS") (62 . 94) (370 . 13) (100 . "AcDbPolyline") (90 . 2) (70 . 0)
(43 . 0.0) (10 17522.6244343891 4027.149321267) (10 17511.3122171946 4027.149321267))
((0 . "LWPOLYLINE") (100 . "AcDbEntity") (8 . "PLANTS") (62 . 94) (370 . 13) (100 . "AcDbPolyline") (90 . 2) (70 . 0)
(43 . 0.0) (10 17511.3122171946 3804.6761312217) (10 17530.1640271493 3804.6761312217))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17515.084841629 882.3529411765 0.0) (10 17557.3348099939 863.1333197544 0.0) (10 17566.1533757411
807.9433864431 0.0) (10 17549.0214932127 769.2307692308 0.0))
((0 . "LWPOLYLINE") (100 . "AcDbEntity") (8 . "PLANTS") (62 . 94) (370 . 13) (100 . "AcDbPolyline") (90 . 3) (70 . 0)
(43 . 0.0) (10 17526.3970588235 946.4564479638) (10 17515.2312217195 901.2075791855) (10 17515.084841629
882.3529411765))
((0 . "LWPOLYLINE") (100 . "AcDbEntity") (8 . "PLANTS") (62 . 94) (370 . 13) (100 . "AcDbPolyline") (90 . 3) (70 . 0)
(43 . 0.0) (10 17549.0214932127 3996.9838235294) (10 17537.8556561086 4004.5311085973) (10 17522.6244343891
4027.149321267))
((0 . "LWPOLYLINE") (100 . "AcDbEntity") (8 . "PLANTS") (62 . 94) (370 . 13) (100 . "AcDbPolyline") (90 . 2) (70 . 0)
(43 . 0.0) (10 17533.9366515837 4038.4615384615) (10 17522.6244343891 4027.149321267))
((0 . "LWPOLYLINE") (100 . "AcDbEntity") (8 . "PLANTS") (62 . 94) (370 . 13) (100 . "AcDbPolyline") (90 . 2) (70 . 0)
(43 . 0.0) (10 17522.6244343891 803.1674208145) (10 17526.3970588235 833.3342760181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17526.3970588235 946.4564479638 0.0) (10 17542.1847460112 992.0543087763 0.0) (10 17572.8378861961
1046.2180070068 0.0) (10 17624.4343891403 1052.0361990951 0.0))
((0 . "LWPOLYLINE") (100 . "AcDbEntity") (8 . "PLANTS") (62 . 94) (370 . 13) (100 . "AcDbPolyline") (90 . 2) (70 . 0)
(43 . 0.0) (10 17526.3970588235 769.2307692308) (10 17526.3970588235 746.6063348416))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17541.4762443439 599.5475113122 0.0) (10 17525.8899058825 591.1629418971 0.0) (10 17519.7096889926
623.4313750236 0.0) (10 17526.3970588235 633.4841628959 0.0))
((0 . "LWPOLYLINE") (100 . "AcDbEntity") (8 . "PLANTS") (62 . 94) (370 . 13) (100 . "AcDbPolyline") (90 . 2) (70 . 0)
(43 . 0.0) (10 17598.0373303167 4095.0226244344) (10 17576.9272594949 4101.9872062248))
((0 . "LWPOLYLINE") (100 . "AcDbEntity") (8 . "PLANTS") (62 . 94) (370 . 13) (100 . "AcDbPolyline") (90 . 3) (70 . 0)
(43 . 0.0) (10 17560.3337104072 3804.6761312217) (10 17549.0214932127 3800.9180995475) (10 17530.1640271493
3804.6761312217))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5783529806) (40
. 1) (40 . 1) (40 . 1) (40 . 1) (10 17530.1640271493 3804.6761312218 0.0) (10 17530.0729976411 3828.2272390821 0.0) (10
17573.9740935629 3862.9874985729 0.0) (10 17616.8691306587 3855.209627633 0.0) (10 17620.661764706 3834.8416289594 0.0))
((0 . "LWPOLYLINE") (100 . "AcDbEntity") (8 . "PLANTS") (62 . 94) (370 . 13) (100 . "AcDbPolyline") (90 . 2) (70 . 0)
(43 . 0.0) (10 17530.1640271493 1108.5972850679) (10 17560.3337104072 1110.4835972851))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17533.9366515837 4038.4615384615 0.0) (10 17558.8962951527 4047.8999715446 0.0) (10 17582.0397835765
4027.9017761235 0.0) (10 17582.9581447964 4004.5248868778 0.0))
((0 . "LWPOLYLINE") (100 . "AcDbEntity") (8 . "PLANTS") (62 . 94) (370 . 13) (100 . "AcDbPolyline") (90 . 3) (70 . 0)
(43 . 0.0) (10 17556.5610859729 558.068438914) (10 17545.2557692308 555.6519230769) (10 17533.9366515837 573.153280543))
((0 . "LWPOLYLINE") (100 . "AcDbEntity") (8 . "PLANTS") (62 . 94) (370 . 13) (100 . "AcDbPolyline") (90 . 2) (70 . 0)
(43 . 0.0) (10 17537.7092760181 1055.8059954751) (10 17541.4762443439 1040.7239819005))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17560.3337104072 1110.4835972851 0.0) (10 17558.1203748725 1093.1547598868 0.0) (10 17558.2900573906
1064.3424849642 0.0) (10 17537.7092760181 1055.8059954751 0.0))
((0 . "LWPOLYLINE") (100 . "AcDbEntity") (8 . "PLANTS") (62 . 94) (370 . 13) (100 . "AcDbPolyline") (90 . 2) (70 . 0)
(43 . 0.0) (10 17552.7884615385 1251.8863122172) (10 17544.9922448086 1260.6124762477))
((0 . "LWPOLYLINE") (100 . "AcDbEntity") (8 . "PLANTS") (62 . 94) (370 . 13) (100 . "AcDbPolyline") (90 . 2) (70 . 0)
(43 . 0.0) (10 17549.0214932127 3996.9838235294) (10 17564.100678733 3947.963800905))
((0 . "LWPOLYLINE") (100 . "AcDbEntity") (8 . "PLANTS") (62 . 94) (370 . 13) (100 . "AcDbPolyline") (90 . 2) (70 . 0)
(43 . 0.0) (10 17549.0214932127 3996.9838235294) (10 17582.9581447964 4004.5248868778))
((0 . "LWPOLYLINE") (100 . "AcDbEntity") (8 . "PLANTS") (62 . 94) (370 . 13) (100 . "AcDbPolyline") (90 . 2) (70 . 0)
(43 . 0.0) (10 17560.3337104072 1110.4835972851) (10 17549.0214932127 1165.1583710407))
((0 . "LWPOLYLINE") (100 . "AcDbEntity") (8 . "PLANTS") (62 . 94) (370 . 13) (100 . "AcDbPolyline") (90 . 2) (70 . 0)
(43 . 0.0) (10 17549.0214932127 1165.1583710407) (10 17556.5610859729 1191.55260181))
((0 . "LWPOLYLINE") (100 . "AcDbEntity") (8 . "PLANTS") (62 . 94) (370 . 13) (100 . "AcDbPolyline") (90 . 2) (70 . 0)
(43 . 0.0) (10 17552.7884615385 1251.8863122172) (10 17556.5610859729 1191.55260181))
((0 . "LWPOLYLINE") (100 . "AcDbEntity") (8 . "PLANTS") (62 . 94) (370 . 13) (100 . "AcDbPolyline") (90 . 2) (70 . 0)
(43 . 0.0) (10 17552.7884615385 1251.8863122172) (10 17571.6459276018 1259.4259049774))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17564.100678733 629.7143665158 0.0) (10 17548.5864391615 638.2093289507 0.0) (10 17544.6127555485
660.2330741551 0.0) (10 17552.7884615385 674.9632352941 0.0))
((0 . "LWPOLYLINE") (100 . "AcDbEntity") (8 . "PLANTS") (62 . 94) (370 . 13) (100 . "AcDbPolyline") (90 . 2) (70 . 0)
(43 . 0.0) (10 17556.5610859729 1191.55260181) (10 17609.3495475113 1187.7828054299))
((0 . "LWPOLYLINE") (100 . "AcDbEntity") (8 . "PLANTS") (62 . 94) (370 . 13) (100 . "AcDbPolyline") (90 . 2) (70 . 0)
(43 . 0.0) (10 17556.5610859729 893.665158371) (10 17564.100678733 946.4564479638))
((0 . "LWPOLYLINE") (100 . "AcDbEntity") (8 . "PLANTS") (62 . 94) (370 . 13) (100 . "AcDbPolyline") (90 . 3) (70 . 0)
(43 . 0.0) (10 17560.3337104072 3740.5727375566) (10 17561.5364253394 3717.9489819005) (10 17571.6459276018
3706.6360859729))
((0 . "SPLINE") (100 . "AcDbEntity") (8 . "PLANTS") (62 . 94) (370 . 13) (100 . "AcDbSpline") (70 . 0) (71 . 3) (72 .
12) (73 . 8) (74 . 0) (42 . 0.0000001) (43 . 0.0000001) (40 . 0.0) (40 . 0.0) (40 . 0.0) (40 . 0.0) (40 . 0.1790780648)
(40 . 0.1984311423) (40 . 0.4170308592) (40 . 0.8247753937) (40 . 1) (40 . 1) (40 . 1) (40 . 1) (10 17560.3337104072
3740.5727375566 0.0) (10 17570.3925292046 3742.2189104544 0.0) (10 17615.5666294448 3759.7458807306 0.0) (10
17646.7903276251 3722.7769098882 0.0) (10 17617.9084894292 3624.5086043463 0.0) (10 17635.4345019125 3534.7011008607
0.0) (10 17635.1694413909 3457.583432223 0.0) (10 17620.6617647059 3438.9140271493 0.0))
((0 . "LWPOLYLINE") (100 . "AcDbEntity") (8 . "PLANTS") (62 . 94) (370 . 13) (100 . "AcDbPolyline") (90 . 2) (70 . 0)
(43 . 0.0) (10 17560.3337104072 1110.4835972851) (10 17616.8947963801 1131.221719457))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17613.1221719457 3906.4860859729 0.0) (10 17606.005540648 3926.927517349 0.0) (10 17590.3300306864
3952.8915532034 0.0) (10 17564.100678733 3947.963800905 0.0))
((0 . "LWPOLYLINE") (100 . "AcDbEntity") (8 . "PLANTS") (62 . 94) (370 . 13) (100 . "AcDbPolyline") (90 . 3) (70 . 0)
(43 . 0.0) (10 17571.6459276018 3902.7149321267) (10 17564.2567873303 3917.7983031674) (10 17564.100678733
3947.963800905))
((0 . "LWPOLYLINE") (100 . "AcDbEntity") (8 . "PLANTS") (62 . 94) (370 . 13) (100 . "AcDbPolyline") (90 . 3) (70 . 0)
(43 . 0.0) (10 17613.1221719457 3906.4860859729) (10 17605.5742081448 3902.8630090498) (10 17571.6459276018
3902.7149321267))
((0 . "LWPOLYLINE") (100 . "AcDbEntity") (8 . "PLANTS") (62 . 94) (370 . 13) (100 . "AcDbPolyline") (90 . 2) (70 . 0)
(43 . 0.0) (10 17609.3495475113 3823.5294117647) (10 17579.185520362 3819.7582579186))
((0 . "LWPOLYLINE") (100 . "AcDbEntity") (8 . "PLANTS") (62 . 94) (370 . 13) (100 . "AcDbPolyline") (90 . 2) (70 . 0)
(43 . 0.0) (10 17601.8099547511 4000.7537330317) (10 17582.9581447964 4004.5248868778))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17598.0373303168 4095.0226244344 0.0) (10 17593.275466355 4060.5283472032 0.0) (10 17626.9601220476
4038.4447601017 0.0) (10 17624.4343891403 4004.5248868778 0.0))
((0 . "LWPOLYLINE") (100 . "AcDbEntity") (8 . "PLANTS") (62 . 94) (370 . 13) (100 . "AcDbPolyline") (90 . 2) (70 . 0)
(43 . 0.0) (10 17598.0373303167 4095.0226244344) (10 17609.3495475113 4098.7937782805))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17639.5192307692 3978.1292986426 0.0) (10 17624.6953929905 3958.0129702733 0.0) (10 17582.1272949377
3973.7688402791 0.0) (10 17601.8099547511 4000.7537330317 0.0))
((0 . "LWPOLYLINE") (100 . "AcDbEntity") (8 . "PLANTS") (62 . 94) (370 . 13) (100 . "AcDbPolyline") (90 . 2) (70 . 0)
(43 . 0.0) (10 17624.4343891403 4004.5248868778) (10 17601.8099547511 4000.7537330317))
((0 . "LWPOLYLINE") (100 . "AcDbEntity") (8 . "PLANTS") (62 . 94) (370 . 13) (100 . "AcDbPolyline") (90 . 2) (70 . 0)
(43 . 0.0) (10 17613.1221719457 3797.1338235294) (10 17601.8099547511 3782.0516968326))
((0 . "LWPOLYLINE") (100 . "AcDbEntity") (8 . "PLANTS") (62 . 94) (370 . 13) (100 . "AcDbPolyline") (90 . 2) (70 . 0)
(43 . 0.0) (10 17601.8099547511 3431.3722850679) (10 17620.6617647059 3438.9140271493))
((0 . "LWPOLYLINE") (100 . "AcDbEntity") (8 . "PLANTS") (62 . 94) (370 . 13) (100 . "AcDbPolyline") (90 . 2) (70 . 0)
(43 . 0.0) (10 17628.2070135747 927.6018099548) (10 17601.8099547511 927.6018099548))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17601.8099547511 927.6018099548 0.0) (10 17588.3392179161 900.9690492877 0.0) (10 17609.7880475133
867.4891241004 0.0) (10 17639.5192307692 863.4983031674 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4103288318) (40
. 1) (40 . 1) (40 . 1) (40 . 1) (10 17624.4343891404 1052.036199095 0.0) (10 17624.2677954661 1034.5101104184 0.0) (10
17604.4528039445 995.3402157687 0.0) (10 17587.5666572086 955.3639087909 0.0) (10 17601.8099547512 927.6018099547 0.0))
((0 . "LWPOLYLINE") (100 . "AcDbEntity") (8 . "PLANTS") (62 . 94) (370 . 13) (100 . "AcDbPolyline") (90 . 2) (70 . 0)
(43 . 0.0) (10 17624.4343891403 829.5616515837) (10 17605.5825791855 833.3342760181))
((0 . "LWPOLYLINE") (100 . "AcDbEntity") (8 . "PLANTS") (62 . 94) (370 . 13) (100 . "AcDbPolyline") (90 . 2) (70 . 0)
(43 . 0.0) (10 17609.3504397745 4126.9281141321) (10 17609.3495475113 4098.7937782805))
((0 . "LWPOLYLINE") (100 . "AcDbEntity") (8 . "PLANTS") (62 . 94) (370 . 13) (100 . "AcDbPolyline") (90 . 2) (70 . 0)
(43 . 0.0) (10 17662.1436651584 4102.5636877828) (10 17609.3495475113 4098.7937782805))
((0 . "LWPOLYLINE") (100 . "AcDbEntity") (8 . "PLANTS") (62 . 94) (370 . 13) (100 . "AcDbPolyline") (90 . 2) (70 . 0)
(43 . 0.0) (10 17609.3495475113 3823.5294117647) (10 17613.1221719457 3797.1338235294))
((0 . "LWPOLYLINE") (100 . "AcDbEntity") (8 . "PLANTS") (62 . 94) (370 . 13) (100 . "AcDbPolyline") (90 . 2) (70 . 0)
(43 . 0.0) (10 17609.3495475113 3823.5294117647) (10 17620.6617647059 3834.8416289593))
((0 . "LWPOLYLINE") (100 . "AcDbEntity") (8 . "PLANTS") (62 . 94) (370 . 13) (100 . "AcDbPolyline") (90 . 3) (70 . 0)
(43 . 0.0) (10 17616.8947963801 1165.1583710407) (10 17610.5481900453 1172.7056561086) (10 17609.3495475113
1187.7828054299))
((0 . "LWPOLYLINE") (100 . "AcDbEntity") (8 . "PLANTS") (62 . 94) (370 . 13) (100 . "AcDbPolyline") (90 . 3) (70 . 0)
(43 . 0.0) (10 17613.1221719457 1217.9496606335) (10 17609.4987556561 1210.4003393665) (10 17609.3495475113
1187.7828054299))
((0 . "LWPOLYLINE") (100 . "AcDbEntity") (8 . "PLANTS") (62 . 94) (370 . 13) (100 . "AcDbPolyline") (90 . 2) (70 . 0)
(43 . 0.0) (10 17613.1221719457 3906.4860859729) (10 17620.6617647059 3906.4860859729))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17652.7149321267 3829.185520362 0.0) (10 17653.1783836746 3809.5076185997 0.0) (10 17626.1277195995
3802.0981684537 0.0) (10 17613.1221719457 3797.1338235294 0.0))
((0 . "LWPOLYLINE") (100 . "AcDbEntity") (8 . "PLANTS") (62 . 94) (370 . 13) (100 . "AcDbPolyline") (90 . 2) (70 . 0)
(43 . 0.0) (10 17626.6968325792 1312.2171945701) (10 17665.9106334842 1312.2171945701))
((0 . "LWPOLYLINE") (100 . "AcDbEntity") (8 . "PLANTS") (62 . 94) (370 . 13) (100 . "AcDbPolyline") (90 . 3) (70 . 0)
(43 . 0.0) (10 17613.1221719457 1217.9496606335) (10 17609.3495475113 1255.6561085973) (10 17609.4924180331
1298.9830295347))
((0 . "LWPOLYLINE") (100 . "AcDbEntity") (8 . "PLANTS") (62 . 94) (370 . 13) (100 . "AcDbPolyline") (90 . 3) (70 . 0)
(43 . 0.0) (10 17613.1221719457 1217.9496606335) (10 17624.4343891403 1214.3254524887) (10 17669.6832579186
1214.1770361991))
((0 . "LWPOLYLINE") (100 . "AcDbEntity") (8 . "PLANTS") (62 . 94) (370 . 13) (100 . "AcDbPolyline") (90 . 2) (70 . 0)
(43 . 0.0) (10 17613.1221719457 573.153280543) (10 17635.7466063348 576.9230769231))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17616.8947963802 3246.6063348416 0.0) (10 17626.4028657953 3186.7307034461 0.0) (10 17594.688422365
3120.3426811054 0.0) (10 17620.6617647059 3061.8403846154 0.0))
((0 . "LWPOLYLINE") (100 . "AcDbEntity") (8 . "PLANTS") (62 . 94) (370 . 13) (100 . "AcDbPolyline") (90 . 2) (70 . 0)
(43 . 0.0) (10 17616.8947963801 1165.1583710407) (10 17654.5984162896 1161.3885746606))
((0 . "LWPOLYLINE") (100 . "AcDbEntity") (8 . "PLANTS") (62 . 94) (370 . 13) (100 . "AcDbPolyline") (90 . 2) (70 . 0)
(43 . 0.0) (10 17616.8947963801 1131.221719457) (10 17616.8947963801 1165.1583710407))
((0 . "LWPOLYLINE") (100 . "AcDbEntity") (8 . "PLANTS") (62 . 94) (370 . 13) (100 . "AcDbPolyline") (90 . 3) (70 . 0)
(43 . 0.0) (10 17665.9106334842 1119.9095022624) (10 17628.2070135747 1123.8346153846) (10 17616.8947963801
1131.221719457))
((0 . "LWPOLYLINE") (100 . "AcDbEntity") (8 . "PLANTS") (62 . 94) (370 . 13) (100 . "AcDbPolyline") (90 . 3) (70 . 0)
(43 . 0.0) (10 17647.0588235294 3895.1738687783) (10 17635.7466063348 3896.2299773756) (10 17620.6617647059
3906.4860859729))
((0 . "LWPOLYLINE") (100 . "AcDbEntity") (8 . "PLANTS") (62 . 94) (370 . 13) (100 . "AcDbPolyline") (90 . 3) (70 . 0)
(43 . 0.0) (10 17665.9106334842 3955.5048642534) (10 17647.206561086 3940.4227375566) (10 17620.6617647059
3906.4860859729))
((0 . "LWPOLYLINE") (100 . "AcDbEntity") (8 . "PLANTS") (62 . 94) (370 . 13) (100 . "AcDbPolyline") (90 . 2) (70 . 0)
(43 . 0.0) (10 17652.7149321267 3829.185520362) (10 17620.6617647059 3834.8416289593))
((0 . "LWPOLYLINE") (100 . "AcDbEntity") (8 . "PLANTS") (62 . 94) (370 . 13) (100 . "AcDbPolyline") (90 . 2) (70 . 0)
(43 . 0.0) (10 17635.7466063348 3427.6018099548) (10 17620.6617647059 3438.9140271493))
((0 . "LWPOLYLINE") (100 . "AcDbEntity") (8 . "PLANTS") (62 . 94) (370 . 13) (100 . "AcDbPolyline") (90 . 2) (70 . 0)
(43 . 0.0) (10 17624.4343891403 4004.5248868778) (10 17639.5192307692 3978.1292986425))
((0 . "LWPOLYLINE") (100 . "AcDbEntity") (8 . "PLANTS") (62 . 94) (370 . 13) (100 . "AcDbPolyline") (90 . 3) (70 . 0)
(43 . 0.0) (10 17665.9106334842 1074.6606334842) (10 17639.5192307692 1069.8337104072) (10 17624.4343891403
1052.036199095))
((0 . "LWPOLYLINE") (100 . "AcDbEntity") (8 . "PLANTS") (62 . 94) (370 . 13) (100 . "AcDbPolyline") (90 . 2) (70 . 0)
(43 . 0.0) (10 17624.4343891403 829.5616515837) (10 17635.7466063348 806.9372171946))
((0 . "LWPOLYLINE") (100 . "AcDbEntity") (8 . "PLANTS") (62 . 94) (370 . 13) (100 . "AcDbPolyline") (90 . 3) (70 . 0)
(43 . 0.0) (10 17624.4343891403 829.5616515837) (10 17629.2619909502 848.4162895928) (10 17639.5192307692
863.4983031674))
((0 . "LWPOLYLINE") (100 . "AcDbEntity") (8 . "PLANTS") (62 . 94) (370 . 13) (100 . "AcDbPolyline") (90 . 2) (70 . 0)
(43 . 0.0) (10 17624.4343891403 629.7143665158) (10 17639.5192307692 633.4841628959))
((0 . "LWPOLYLINE") (100 . "AcDbEntity") (8 . "PLANTS") (62 . 94) (370 . 13) (100 . "AcDbPolyline") (90 . 3) (70 . 0)
(43 . 0.0) (10 17677.2228506787 920.0593891403) (10 17654.5984162896 920.2078054299) (10 17628.2070135747
927.6018099548))
((0 . "LWPOLYLINE") (100 . "AcDbEntity") (8 . "PLANTS") (62 . 94) (370 . 13) (100 . "AcDbPolyline") (90 . 3) (70 . 0)
(43 . 0.0) (10 17658.371040724 957.7686651584) (10 17643.4367647059 950.0778280543) (10 17628.2070135747
927.6018099548))
((0 . "LWPOLYLINE") (100 . "AcDbEntity") (8 . "PLANTS") (62 . 94) (370 . 13) (100 . "AcDbPolyline") (90 . 3) (70 . 0)
(43 . 0.0) (10 17631.9739819005 739.0639140271) (10 17632.1231900452 686.2754524887) (10 17643.286199095
663.6510180995))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17631.9739819004 739.0639140272 0.0) (10 17593.6648168083 733.936914677 0.0) (10 17623.1118563885
812.9175240052 0.0) (10 17635.7466063348 806.9372171946 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17631.9739819005 739.0639140271 0.0) (10 17659.3451254216 745.1622873424 0.0) (10 17687.5132278191
779.4324937221 0.0) (10 17658.371040724 806.9372171946 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17635.7466063348 3314.4796380091 0.0) (10 17653.1957678857 3354.908521532 0.0) (10 17608.8111524083
3386.6576262443 0.0) (10 17635.7466063348 3427.6018099548 0.0))
((0 . "LWPOLYLINE") (100 . "AcDbEntity") (8 . "PLANTS") (62 . 94) (370 . 13) (100 . "AcDbPolyline") (90 . 2) (70 . 0)
(43 . 0.0) (10 17635.7466063348 3427.6018099548) (10 17647.0588235294 3435.1435520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17635.7466063349 3314.479638009 0.0) (10 17658.7066614462 3301.9364541608 0.0) (10 17690.067353117
3324.5678567246 0.0) (10 17707.3925339367 3299.3969457014 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3655831914) (40
. 1) (40 . 1) (40 . 1) (40 . 1) (10 17635.7466063348 3314.4796380091 0.0) (10 17615.2035000464 3300.3289078495 0.0) (10
17632.0710702066 3271.5449113035 0.0) (10 17693.8539759368 3281.2207596752 0.0) (10 17707.3925339366 3299.3969457014
0.0))
((0 . "LWPOLYLINE") (100 . "AcDbEntity") (8 . "PLANTS") (62 . 94) (370 . 13) (100 . "AcDbPolyline") (90 . 2) (70 . 0)
(43 . 0.0) (10 17658.371040724 806.9372171946) (10 17635.7466063348 806.9372171946))
((0 . "LWPOLYLINE") (100 . "AcDbEntity") (8 . "PLANTS") (62 . 94) (370 . 13) (100 . "AcDbPolyline") (90 . 2) (70 . 0)
(43 . 0.0) (10 17662.1436651584 3978.1292986425) (10 17639.5192307692 3978.1292986425))
((0 . "LWPOLYLINE") (100 . "AcDbEntity") (8 . "PLANTS") (62 . 94) (370 . 13) (100 . "AcDbPolyline") (90 . 2) (70 . 0)
(43 . 0.0) (10 17679.1119909502 865.3846153846) (10 17639.5192307692 863.4983031674))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17675.3393665158 667.4208144796 0.0) (10 17682.3521057364 647.0077678636 0.0) (10 17670.5258849707
609.1765897766 0.0) (10 17639.5192307692 633.4841628959 0.0))
((0 . "LWPOLYLINE") (100 . "AcDbEntity") (8 . "PLANTS") (62 . 94) (370 . 13) (100 . "AcDbPolyline") (90 . 3) (70 . 0)
(43 . 0.0) (10 17643.286199095 663.6510180995) (10 17639.6656108597 656.1016968326) (10 17639.5192307692
633.4841628959))
((0 . "LWPOLYLINE") (100 . "AcDbEntity") (8 . "PLANTS") (62 . 94) (370 . 13) (100 . "AcDbPolyline") (90 . 3) (70 . 0)
(43 . 0.0) (10 17675.3393665158 667.4208144796) (10 17650.835520362 667.2730769231) (10 17643.286199095 663.6510180995))
((0 . "LWPOLYLINE") (100 . "AcDbEntity") (8 . "PLANTS") (62 . 94) (370 . 13) (100 . "AcDbPolyline") (90 . 3) (70 . 0)
(43 . 0.0) (10 17647.0588235294 3895.1738687783) (10 17650.682239819 3887.6253393665) (10 17652.7149321267
3829.185520362))
((0 . "LWPOLYLINE") (100 . "AcDbEntity") (8 . "PLANTS") (62 . 94) (370 . 13) (100 . "AcDbPolyline") (90 . 3) (70 . 0)
(43 . 0.0) (10 17647.0588235294 3895.1738687783) (10 17673.2997737557 3910.4044117647) (10 17688.5350678733
3947.963800905))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.5187596325) (40
. 1) (40 . 1) (40 . 1) (40 . 1) (10 17745.0961538462 3910.2559954751 0.0) (10 17721.740286014 3902.7470180113 0.0) (10
17698.4223244704 3864.8432002191 0.0) (10 17680.238253635 3827.8590067909 0.0) (10 17652.7149321267 3829.185520362 0.0))
((0 . "LWPOLYLINE") (100 . "AcDbEntity") (8 . "PLANTS") (62 . 94) (370 . 13) (100 . "AcDbPolyline") (90 . 3) (70 . 0)
(43 . 0.0) (10 17658.371040724 957.7686651584) (10 17668.4874434389 950.2193438914) (10 17677.2228506787
927.6018099548))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17665.9106334842 1074.6606334842 0.0) (10 17675.4164725651 1034.0428937777 0.0) (10 17638.1387562338
999.8327989705 0.0) (10 17658.371040724 957.7686651584 0.0))
((0 . "LWPOLYLINE") (100 . "AcDbEntity") (8 . "PLANTS") (62 . 94) (370 . 13) (100 . "AcDbPolyline") (90 . 3) (70 . 0)
(43 . 0.0) (10 17658.371040724 806.9372171946) (10 17672.2503393665 818.2570135747) (10 17679.1119909502
865.3846153846))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17662.1436651584 3978.1292986425 0.0) (10 17707.1306838694 4002.8254955269 0.0) (10 17600.6358350798
4096.2655594709 0.0) (10 17662.1436651584 4102.5636877828 0.0))
((0 . "LWPOLYLINE") (100 . "AcDbEntity") (8 . "PLANTS") (62 . 94) (370 . 13) (100 . "AcDbPolyline") (90 . 3) (70 . 0)
(43 . 0.0) (10 17662.1436651584 4102.5636877828) (10 17669.6832579186 4147.8125565611) (10 17669.6832579186
4173.337974243))
((0 . "LWPOLYLINE") (100 . "AcDbEntity") (8 . "PLANTS") (62 . 94) (370 . 13) (100 . "AcDbPolyline") (90 . 2) (70 . 0)
(43 . 0.0) (10 17662.1436651584 3978.1292986425) (10 17665.9106334842 3955.5048642534))
((0 . "LWPOLYLINE") (100 . "AcDbEntity") (8 . "PLANTS") (62 . 94) (370 . 13) (100 . "AcDbPolyline") (90 . 2) (70 . 0)
(43 . 0.0) (10 17662.1436651584 3699.0950226244) (10 17662.1436651584 3691.553959276))
((0 . "LWPOLYLINE") (100 . "AcDbEntity") (8 . "PLANTS") (62 . 94) (370 . 13) (100 . "AcDbPolyline") (90 . 2) (70 . 0)
(43 . 0.0) (10 17665.9106334842 3955.5048642534) (10 17688.5350678733 3947.963800905))
((0 . "LWPOLYLINE") (100 . "AcDbEntity") (8 . "PLANTS") (62 . 94) (370 . 13) (100 . "AcDbPolyline") (90 . 2) (70 . 0)
(43 . 0.0) (10 17665.9106334842 1304.6747737557) (10 17665.9106334842 1312.2171945701))
((0 . "LWPOLYLINE") (100 . "AcDbEntity") (8 . "PLANTS") (62 . 94) (370 . 13) (100 . "AcDbPolyline") (90 . 2) (70 . 0)
(43 . 0.0) (10 17665.9109136748 1342.381872336) (10 17665.9106334842 1312.2171945701))
((0 . "LWPOLYLINE") (100 . "AcDbEntity") (8 . "PLANTS") (62 . 94) (370 . 13) (100 . "AcDbPolyline") (90 . 3) (70 . 0)
(43 . 0.0) (10 17696.0803167421 1289.592760181) (10 17692.1544117647 1303.4713800905) (10 17665.9106334842
1304.6747737557))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17665.9106334842 1304.6747737557 0.0) (10 17666.2454157024 1289.0389731481 0.0) (10 17663.0308426307
1267.1279903101 0.0) (10 17677.2228506787 1255.6561085973 0.0))
((0 . "LWPOLYLINE") (100 . "AcDbEntity") (8 . "PLANTS") (62 . 94) (370 . 13) (100 . "AcDbPolyline") (90 . 2) (70 . 0)
(43 . 0.0) (10 17665.9106334842 1202.8648190045) (10 17669.6832579186 1214.1770361991))
((0 . "LWPOLYLINE") (100 . "AcDbEntity") (8 . "PLANTS") (62 . 94) (370 . 13) (100 . "AcDbPolyline") (90 . 2) (70 . 0)
(43 . 0.0) (10 17665.9106334842 1074.6606334842) (10 17665.9106334842 1119.9095022624))
((0 . "LWPOLYLINE") (100 . "AcDbEntity") (8 . "PLANTS") (62 . 94) (370 . 13) (100 . "AcDbPolyline") (90 . 2) (70 . 0)
(43 . 0.0) (10 17680.9954751131 1127.4519230769) (10 17665.9106334842 1119.9095022624))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17665.9106334842 1074.6606334842 0.0) (10 17686.6923393873 1074.6098385545 0.0) (10 17720.0823153558
1069.8887778301 0.0) (10 17726.2443438914 1044.4937782805 0.0))
((0 . "LWPOLYLINE") (100 . "AcDbEntity") (8 . "PLANTS") (62 . 94) (370 . 13) (100 . "AcDbPolyline") (90 . 3) (70 . 0)
(43 . 0.0) (10 17669.6832579186 3585.9728506787) (10 17677.2312217195 3596.0871040724) (10 17711.1595022624
3604.8268099548))
((0 . "LWPOLYLINE") (100 . "AcDbEntity") (8 . "PLANTS") (62 . 94) (370 . 13) (100 . "AcDbPolyline") (90 . 3) (70 . 0)
(43 . 0.0) (10 17669.6832579186 3533.182239819) (10 17670.7395927602 3518.0995475113) (10 17677.2228506787
3506.7873303167))
((0 . "LWPOLYLINE") (100 . "AcDbEntity") (8 . "PLANTS") (62 . 94) (370 . 13) (100 . "AcDbPolyline") (90 . 3) (70 . 0)
(43 . 0.0) (10 17669.6832579186 1214.1770361991) (10 17677.0764705882 1229.2618778281) (10 17677.2228506787
1255.6561085973))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17673.455882353 3736.8028280543 0.0) (10 17657.5614912323 3764.0734497027 0.0) (10 17686.0321405359
3784.7567182205 0.0) (10 17707.3925339367 3793.3639140271 0.0))
((0 . "LWPOLYLINE") (100 . "AcDbEntity") (8 . "PLANTS") (62 . 94) (370 . 13) (100 . "AcDbPolyline") (90 . 3) (70 . 0)
(43 . 0.0) (10 17673.4558823529 3333.3335972851) (10 17677.2187782805 3367.2702488688) (10 17677.2228506787
3476.6211538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17675.3393665158 667.4208144796 0.0) (10 17666.7210874751 691.1900338201 0.0) (10 17688.8607071305
715.6743694239 0.0) (10 17711.1595022624 720.2121040724 0.0))
((0 . "LWPOLYLINE") (100 . "AcDbEntity") (8 . "PLANTS") (62 . 94) (370 . 13) (100 . "AcDbPolyline") (90 . 3) (70 . 0)
(43 . 0.0) (10 17675.3393665158 667.4208144796) (10 17703.6199095023 676.1666289593) (10 17733.7839366516
705.1272624434))
((0 . "LWPOLYLINE") (100 . "AcDbEntity") (8 . "PLANTS") (62 . 94) (370 . 13) (100 . "AcDbPolyline") (90 . 3) (70 . 0)
(43 . 0.0) (10 17696.0803167421 1266.9683257919) (10 17692.1544117647 1260.4761312217) (10 17677.2228506787
1255.6561085973))
((0 . "LWPOLYLINE") (100 . "AcDbEntity") (8 . "PLANTS") (62 . 94) (370 . 13) (100 . "AcDbPolyline") (90 . 2) (70 . 0)
(43 . 0.0) (10 17677.2228506787 920.0593891403) (10 17677.2228506787 927.6018099548))
((0 . "LWPOLYLINE") (100 . "AcDbEntity") (8 . "PLANTS") (62 . 94) (370 . 13) (100 . "AcDbPolyline") (90 . 3) (70 . 0)
(43 . 0.0) (10 17730.0169683258 931.3716063348) (10 17688.5350678733 931.2245475113) (10 17677.2228506787
927.6018099548))
((0 . "LWPOLYLINE") (100 . "AcDbEntity") (8 . "PLANTS") (62 . 94) (370 . 13) (100 . "AcDbPolyline") (90 . 2) (70 . 0)
(43 . 0.0) (10 17677.2228506787 920.0593891403) (10 17679.1119909502 865.3846153846))
((0 . "LWPOLYLINE") (100 . "AcDbEntity") (8 . "PLANTS") (62 . 94) (370 . 13) (100 . "AcDbPolyline") (90 . 2) (70 . 0)
(43 . 0.0) (10 17679.1119909502 865.3846153846) (10 17714.9321266968 867.2709276018))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17730.0169683258 1116.1397058824 0.0) (10 17713.4463731038 1107.3507879935 0.0) (10 17693.5604704872
1115.8830156677 0.0) (10 17680.9954751131 1127.4519230769 0.0))
((0 . "LWPOLYLINE") (100 . "AcDbEntity") (8 . "PLANTS") (62 . 94) (370 . 13) (100 . "AcDbPolyline") (90 . 3) (70 . 0)
(43 . 0.0) (10 17680.9954751131 1127.4519230769) (10 17688.6856334842 1141.47760181) (10 17714.9321266968
1150.0763574661))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17688.5350678733 3947.963800905 0.0) (10 17730.7074248255 3962.3835597276 0.0) (10 17775.4722894395
3910.9267589669 0.0) (10 17812.9694570136 3944.1926470588 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6415471334) (40
. 1) (40 . 1) (40 . 1) (40 . 1) (10 17746.8863478298 624.6743557743 0.0) (10 17709.1084694394 639.444053044 0.0) (10
17731.5982350634 580.8034074453 0.0) (10 17692.0632682524 564.0310296184 0.0) (10 17692.3076923076 550.5288461539 0.0))
((0 . "LWPOLYLINE") (100 . "AcDbEntity") (8 . "PLANTS") (62 . 94) (370 . 13) (100 . "AcDbPolyline") (90 . 2) (70 . 0)
(43 . 0.0) (10 17696.0803167421 3653.8461538462) (10 17722.471719457 3657.6173076923))
((0 . "LWPOLYLINE") (100 . "AcDbEntity") (8 . "PLANTS") (62 . 94) (370 . 13) (100 . "AcDbPolyline") (90 . 3) (70 . 0)
(43 . 0.0) (10 17737.556561086 3699.0950226244) (10 17718.7047511312 3697.89739819) (10 17703.6199095023
3687.7828054299))
((0 . "LWPOLYLINE") (100 . "AcDbEntity") (8 . "PLANTS") (62 . 94) (370 . 13) (100 . "AcDbPolyline") (90 . 3) (70 . 0)
(43 . 0.0) (10 17714.9321266968 4147.8125565611) (10 17711.1595022624 4151.5837104072) (10 17707.3925339367
4147.8125565611))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4617729638) (40
. 1) (40 . 1) (40 . 1) (40 . 1) (10 17707.3925339368 4072.3981900452 0.0) (10 17707.7762674428 4056.0520569491 0.0) (10
17683.6667860853 4017.4781336962 0.0) (10 17724.0725279023 3992.1568083023 0.0) (10 17745.0961538462 3993.2126696833
0.0))
((0 . "LWPOLYLINE") (100 . "AcDbEntity") (8 . "PLANTS") (62 . 94) (370 . 13) (100 . "AcDbPolyline") (90 . 2) (70 . 0)
(43 . 0.0) (10 17707.3925339367 3808.446040724) (10 17707.3925339367 3793.3639140271))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17752.6414027149 3755.6561085973 0.0) (10 17724.5799233171 3753.5093760781 0.0) (10 17728.3268308942
3787.2875113941 0.0) (10 17707.3925339367 3793.3639140271 0.0))
((0 . "LWPOLYLINE") (100 . "AcDbEntity") (8 . "PLANTS") (62 . 94) (370 . 13) (100 . "AcDbPolyline") (90 . 2) (70 . 0)
(43 . 0.0) (10 17719.3651087077 3299.3969457014) (10 17707.3925339367 3299.3969457014))
((0 . "LWPOLYLINE") (100 . "AcDbEntity") (8 . "PLANTS") (62 . 94) (370 . 13) (100 . "AcDbPolyline") (90 . 2) (70 . 0)
(43 . 0.0) (10 17722.471719457 1331.0718325792) (10 17707.3925339367 1327.2992081448))
((0 . "LWPOLYLINE") (100 . "AcDbEntity") (8 . "PLANTS") (62 . 94) (370 . 13) (100 . "AcDbPolyline") (90 . 2) (70 . 0)
(43 . 0.0) (10 17707.3925339367 731.524321267) (10 17711.1595022624 720.2121040724))
((0 . "LWPOLYLINE") (100 . "AcDbEntity") (8 . "PLANTS") (62 . 94) (370 . 13) (100 . "AcDbPolyline") (90 . 3) (70 . 0)
(43 . 0.0) (10 17718.7047511312 3589.7433257919) (10 17711.1595022624 3597.2850678733) (10 17711.1595022624
3604.8268099548))
((0 . "LWPOLYLINE") (100 . "AcDbEntity") (8 . "PLANTS") (62 . 94) (370 . 13) (100 . "AcDbPolyline") (90 . 3) (70 . 0)
(43 . 0.0) (10 17741.3291855204 3631.221719457) (10 17730.0169683258 3627.2966063348) (10 17711.1595022624
3604.8268099548))
((0 . "LWPOLYLINE") (100 . "AcDbEntity") (8 . "PLANTS") (62 . 94) (370 . 13) (100 . "AcDbPolyline") (90 . 3) (70 . 0)
(43 . 0.0) (10 17718.7047511312 980.3930995475) (10 17718.5486425339 1010.5571266968) (10 17711.1595022624
1021.8693438914))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17718.7047511312 980.3930995475 0.0) (10 17694.6500594777 977.1237841662 0.0) (10 17687.4207297318
1017.0019449503 0.0) (10 17711.1595022624 1021.8693438914 0.0))
((0 . "LWPOLYLINE") (100 . "AcDbEntity") (8 . "PLANTS") (62 . 94) (370 . 13) (100 . "AcDbPolyline") (90 . 2) (70 . 0)
(43 . 0.0) (10 17711.1595022624 1021.8693438914) (10 17726.2443438914 1044.4937782805))
((0 . "LWPOLYLINE") (100 . "AcDbEntity") (8 . "PLANTS") (62 . 94) (370 . 13) (100 . "AcDbPolyline") (90 . 3) (70 . 0)
(43 . 0.0) (10 17733.7839366516 705.1272624434) (10 17718.7088235294 719.007239819) (10 17711.1595022624
720.2121040724))
((0 . "LWPOLYLINE") (100 . "AcDbEntity") (8 . "PLANTS") (62 . 94) (370 . 13) (100 . "AcDbPolyline") (90 . 3) (70 . 0)
(43 . 0.0) (10 17730.0169683258 1116.1397058824) (10 17725.0540723982 1134.9915158371) (10 17714.9321266968
1150.0763574661))
((0 . "LWPOLYLINE") (100 . "AcDbEntity") (8 . "PLANTS") (62 . 94) (370 . 13) (100 . "AcDbPolyline") (90 . 3) (70 . 0)
(43 . 0.0) (10 17737.556561086 1172.7007918552) (10 17716.1363122172 1157.4688914027) (10 17714.9321266968
1150.0763574661))
((0 . "LWPOLYLINE") (100 . "AcDbEntity") (8 . "PLANTS") (62 . 94) (370 . 13) (100 . "AcDbPolyline") (90 . 2) (70 . 0)
(43 . 0.0) (10 17730.0169683258 844.6464932127) (10 17714.9321266968 867.2709276018))
((0 . "LWPOLYLINE") (100 . "AcDbEntity") (8 . "PLANTS") (62 . 94) (370 . 13) (100 . "AcDbPolyline") (90 . 3) (70 . 0)
(43 . 0.0) (10 17737.556561086 889.895361991) (10 17722.4800904977 878.5831447964) (10 17714.9321266968 867.2709276018))
((0 . "LWPOLYLINE") (100 . "AcDbEntity") (8 . "PLANTS") (62 . 94) (370 . 13) (100 . "AcDbPolyline") (90 . 2) (70 . 0)
(43 . 0.0) (10 17718.7047511312 3589.7433257919) (10 17718.7047511312 3574.6606334842))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17718.7047511312 3589.7433257919 0.0) (10 17738.8792429048 3592.6656598279 0.0) (10 17744.7917440739
3614.8200960281 0.0) (10 17741.3291855204 3631.221719457 0.0))
((0 . "LWPOLYLINE") (100 . "AcDbEntity") (8 . "PLANTS") (62 . 94) (370 . 13) (100 . "AcDbPolyline") (90 . 2) (70 . 0)
(43 . 0.0) (10 17718.7047511312 980.3930995475) (10 17752.6414027149 953.996040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17722.471719457 4117.6470588235 0.0) (10 17714.7132068859 4093.8684416141 0.0) (10 17736.8042123963
4067.6490528744 0.0) (10 17760.1809954751 4072.3981900452 0.0))
((0 . "LWPOLYLINE") (100 . "AcDbEntity") (8 . "PLANTS") (62 . 94) (370 . 13) (100 . "AcDbPolyline") (90 . 2) (70 . 0)
(43 . 0.0) (10 17722.471719457 3657.6173076923) (10 17741.3291855204 3638.7627828054))
((0 . "LWPOLYLINE") (100 . "AcDbEntity") (8 . "PLANTS") (62 . 94) (370 . 13) (100 . "AcDbPolyline") (90 . 2) (70 . 0)
(43 . 0.0) (10 17750.7522624434 3689.667760181) (10 17722.471719457 3657.6173076923))
((0 . "LWPOLYLINE") (100 . "AcDbEntity") (8 . "PLANTS") (62 . 94) (370 . 13) (100 . "AcDbPolyline") (90 . 2) (70 . 0)
(43 . 0.0) (10 17722.471719457 3363.4989819005) (10 17730.0169683258 3355.9580316742))
((0 . "LWPOLYLINE") (100 . "AcDbEntity") (8 . "PLANTS") (62 . 94) (370 . 13) (100 . "AcDbPolyline") (90 . 2) (70 . 0)
(43 . 0.0) (10 17726.2443438914 3842.3826923077) (10 17741.3291855204 3842.3826923077))
((0 . "LWPOLYLINE") (100 . "AcDbEntity") (8 . "PLANTS") (62 . 94) (370 . 13) (100 . "AcDbPolyline") (90 . 2) (70 . 0)
(43 . 0.0) (10 17726.2443438914 1289.592760181) (10 17730.0169683258 1300.9049773756))
((0 . "LWPOLYLINE") (100 . "AcDbEntity") (8 . "PLANTS") (62 . 94) (370 . 13) (100 . "AcDbPolyline") (90 . 2) (70 . 0)
(43 . 0.0) (10 17756.4083710407 1044.4937782805) (10 17726.2443438914 1044.4937782805))
((0 . "LWPOLYLINE") (100 . "AcDbEntity") (8 . "PLANTS") (62 . 94) (370 . 13) (100 . "AcDbPolyline") (90 . 2) (70 . 0)
(43 . 0.0) (10 17730.0169683258 1270.7381221719) (10 17737.556561086 1259.4259049774))
((0 . "LWPOLYLINE") (100 . "AcDbEntity") (8 . "PLANTS") (62 . 94) (370 . 13) (100 . "AcDbPolyline") (90 . 3) (70 . 0)
(43 . 0.0) (10 17730.0169683258 1116.1397058824) (10 17760.1809954751 1116.2929864253) (10 17775.2658371041
1127.4519230769))
((0 . "LWPOLYLINE") (100 . "AcDbEntity") (8 . "PLANTS") (62 . 94) (370 . 13) (100 . "AcDbPolyline") (90 . 2) (70 . 0)
(43 . 0.0) (10 17737.556561086 889.895361991) (10 17730.0169683258 931.3716063348))
((0 . "LWPOLYLINE") (100 . "AcDbEntity") (8 . "PLANTS") (62 . 94) (370 . 13) (100 . "AcDbPolyline") (90 . 2) (70 . 0)
(43 . 0.0) (10 17730.0169683258 931.3716063348) (10 17752.6414027149 953.996040724))
((0 . "LWPOLYLINE") (100 . "AcDbEntity") (8 . "PLANTS") (62 . 94) (370 . 13) (100 . "AcDbPolyline") (90 . 2) (70 . 0)
(43 . 0.0) (10 17730.0169683258 844.6464932127) (10 17730.0169683258 814.479638009))
((0 . "LWPOLYLINE") (100 . "AcDbEntity") (8 . "PLANTS") (62 . 94) (370 . 13) (100 . "AcDbPolyline") (90 . 2) (70 . 0)
(43 . 0.0) (10 17730.0169683258 844.6464932127) (10 17764.4548459962 844.7685966928))
((0 . "LWPOLYLINE") (100 . "AcDbEntity") (8 . "PLANTS") (62 . 94) (370 . 13) (100 . "AcDbPolyline") (90 . 3) (70 . 0)
(43 . 0.0) (10 17760.9786617217 801.2197325876) (10 17748.8687782805 809.6589366516) (10 17730.0169683258
814.479638009))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17756.4083710407 765.4609728507 0.0) (10 17716.7369720382 735.9922084585 0.0) (10 17693.7218058776
800.7342601292 0.0) (10 17730.0169683258 814.479638009 0.0))
((0 . "LWPOLYLINE") (100 . "AcDbEntity") (8 . "PLANTS") (62 . 94) (370 . 13) (100 . "AcDbPolyline") (90 . 2) (70 . 0)
(43 . 0.0) (10 17733.7839366516 4042.2326923077) (10 17733.7839366516 4034.6903846154))
((0 . "LWPOLYLINE") (100 . "AcDbEntity") (8 . "PLANTS") (62 . 94) (370 . 13) (100 . "AcDbPolyline") (90 . 2) (70 . 0)
(43 . 0.0) (10 17745.0961538462 705.1272624434) (10 17733.7839366516 705.1272624434))
((0 . "LWPOLYLINE") (100 . "AcDbEntity") (8 . "PLANTS") (62 . 94) (370 . 13) (100 . "AcDbPolyline") (90 . 2) (70 . 0)
(43 . 0.0) (10 17750.7522624434 3689.667760181) (10 17737.556561086 3699.0950226244))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17737.556561086 3699.0950226244 0.0) (10 17735.1053408377 3711.1677490429 0.0) (10 17737.2737215841
3733.0407493138 0.0) (10 17752.6414027149 3736.8028280543 0.0))
((0 . "LWPOLYLINE") (100 . "AcDbEntity") (8 . "PLANTS") (62 . 94) (370 . 13) (100 . "AcDbPolyline") (90 . 2) (70 . 0)
(43 . 0.0) (10 17752.6414027149 1259.4259049774) (10 17737.556561086 1259.4259049774))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17737.5565610859 1172.7007918552 0.0) (10 17721.442374097 1195.1244330874 0.0) (10 17720.5620098444
1236.7375762561 0.0) (10 17737.5565610859 1259.4259049774 0.0))
((0 . "LWPOLYLINE") (100 . "AcDbEntity") (8 . "PLANTS") (62 . 94) (370 . 13) (100 . "AcDbPolyline") (90 . 2) (70 . 0)
(43 . 0.0) (10 17737.556561086 1172.7007918552) (10 17756.4083710407 1172.7007918552))
((0 . "LWPOLYLINE") (100 . "AcDbEntity") (8 . "PLANTS") (62 . 94) (370 . 13) (100 . "AcDbPolyline") (90 . 2) (70 . 0)
(43 . 0.0) (10 17737.556561086 889.895361991) (10 17767.8553377315 887.3692014881))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17752.6414027149 3755.6561085973 0.0) (10 17772.9384692006 3781.3484492038 0.0) (10 17752.8528263831
3818.2191555677 0.0) (10 17741.3291855204 3842.3826923077 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17741.3291855204 3842.3826923077 0.0) (10 17742.061482499 3866.005563859 0.0) (10 17770.4082772503
3877.4607414719 0.0) (10 17790.3450226244 3876.3193438914 0.0))
((0 . "LWPOLYLINE") (100 . "AcDbEntity") (8 . "PLANTS") (62 . 94) (370 . 13) (100 . "AcDbPolyline") (90 . 2) (70 . 0)
(43 . 0.0) (10 17748.8687782805 3638.7627828054) (10 17741.3291855204 3638.7627828054))
((0 . "LWPOLYLINE") (100 . "AcDbEntity") (8 . "PLANTS") (62 . 94) (370 . 13) (100 . "AcDbPolyline") (90 . 2) (70 . 0)
(43 . 0.0) (10 17741.3291855204 3631.221719457) (10 17741.3291855204 3638.7627828054))
((0 . "LWPOLYLINE") (100 . "AcDbEntity") (8 . "PLANTS") (62 . 94) (370 . 13) (100 . "AcDbPolyline") (90 . 3) (70 . 0)
(43 . 0.0) (10 17775.2658371041 3981.9004524887) (10 17749.0220588235 3986.8623303167) (10 17745.0961538462
3993.2126696833))
((0 . "LWPOLYLINE") (100 . "AcDbEntity") (8 . "PLANTS") (62 . 94) (370 . 13) (100 . "AcDbPolyline") (90 . 3) (70 . 0)
(43 . 0.0) (10 17763.9536199095 4012.0659502262) (10 17752.7877828054 4007.2393665158) (10 17745.0961538462
3993.2126696833))
((0 . "LWPOLYLINE") (100 . "AcDbEntity") (8 . "PLANTS") (62 . 94) (370 . 13) (100 . "AcDbPolyline") (90 . 2) (70 . 0)
(43 . 0.0) (10 17745.0961538462 705.1272624434) (10 17752.0853875126 689.8067695789))
((0 . "LWPOLYLINE") (100 . "AcDbEntity") (8 . "PLANTS") (62 . 94) (370 . 13) (100 . "AcDbPolyline") (90 . 2) (70 . 0)
(43 . 0.0) (10 17745.0961538462 705.1272624434) (10 17755.1058316607 727.6462226561))
((0 . "LWPOLYLINE") (100 . "AcDbEntity") (8 . "PLANTS") (62 . 94) (370 . 13) (100 . "AcDbPolyline") (90 . 2) (70 . 0)
(43 . 0.0) (10 17748.8687782805 3638.7627828054) (10 17761.1992083003 3632.0369897565))
((0 . "LWPOLYLINE") (100 . "AcDbEntity") (8 . "PLANTS") (62 . 94) (370 . 13) (100 . "AcDbPolyline") (90 . 2) (70 . 0)
(43 . 0.0) (10 17748.8687782805 3638.7627828054) (10 17763.9536199095 3672.6994343891))
((0 . "LWPOLYLINE") (100 . "AcDbEntity") (8 . "PLANTS") (62 . 94) (370 . 13) (100 . "AcDbPolyline") (90 . 2) (70 . 0)
(43 . 0.0) (10 17750.7522624434 3689.667760181) (10 17763.9536199095 3672.6994343891))
((0 . "LWPOLYLINE") (100 . "AcDbEntity") (8 . "PLANTS") (62 . 94) (370 . 13) (100 . "AcDbPolyline") (90 . 2) (70 . 0)
(43 . 0.0) (10 17750.7522624434 3689.667760181) (10 17767.4426542981 3710.2534937843))
((0 . "LWPOLYLINE") (100 . "AcDbEntity") (8 . "PLANTS") (62 . 94) (370 . 13) (100 . "AcDbPolyline") (90 . 3) (70 . 0)
(43 . 0.0) (10 17767.5069019574 3711.0583741825) (10 17766.5178733032 3721.7194570136) (10 17752.6414027149
3736.8028280543))
((0 . "LWPOLYLINE") (100 . "AcDbEntity") (8 . "PLANTS") (62 . 94) (370 . 13) (100 . "AcDbPolyline") (90 . 2) (70 . 0)
(43 . 0.0) (10 17752.6414027149 3748.1150452489) (10 17752.6414027149 3755.6561085973))
((0 . "LWPOLYLINE") (100 . "AcDbEntity") (8 . "PLANTS") (62 . 94) (370 . 13) (100 . "AcDbPolyline") (90 . 2) (70 . 0)
(43 . 0.0) (10 17752.6414027149 3748.1150452489) (10 17794.1176470588 3748.1150452489))
((0 . "LWPOLYLINE") (100 . "AcDbEntity") (8 . "PLANTS") (62 . 94) (370 . 13) (100 . "AcDbPolyline") (90 . 2) (70 . 0)
(43 . 0.0) (10 17752.6414027149 3748.1150452489) (10 17752.6414027149 3736.8028280543))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.3531506126) (40
. 1) (40 . 1) (40 . 1) (40 . 1) (10 17756.4083710408 1172.7007918552 0.0) (10 17761.8715890086 1182.0003552206 0.0) (10
17761.8821759852 1211.0965915994 0.0) (10 17765.4523573688 1244.2121754249 0.0) (10 17752.641402715 1259.4259049774
0.0))
((0 . "LWPOLYLINE") (100 . "AcDbEntity") (8 . "PLANTS") (62 . 94) (370 . 13) (100 . "AcDbPolyline") (90 . 2) (70 . 0)
(43 . 0.0) (10 17763.9536199095 1285.8229638009) (10 17752.6414027149 1259.4259049774))
((0 . "LWPOLYLINE") (100 . "AcDbEntity") (8 . "PLANTS") (62 . 94) (370 . 13) (100 . "AcDbPolyline") (90 . 3) (70 . 0)
(43 . 0.0) (10 17752.6414027149 953.996040724) (10 17763.9452488688 954.2191176471) (10 17771.4932126697
959.6521493213))
((0 . "LWPOLYLINE") (100 . "AcDbEntity") (8 . "PLANTS") (62 . 94) (370 . 13) (100 . "AcDbPolyline") (90 . 3) (70 . 0)
(43 . 0.0) (10 17756.4083710407 1172.7007918552) (10 17761.2304298643 1150.0763574661) (10 17775.2658371041
1127.4519230769))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17771.4932126697 959.6521493213 0.0) (10 17752.2818656381 985.6761973426 0.0) (10 17776.7283230518
1020.073367494 0.0) (10 17756.4083710407 1044.4937782805 0.0))
((0 . "LWPOLYLINE") (100 . "AcDbEntity") (8 . "PLANTS") (62 . 94) (370 . 13) (100 . "AcDbPolyline") (90 . 3) (70 . 0)
(43 . 0.0) (10 17786.5780542986 1059.5786199095) (10 17767.7205882353 1054.60260181) (10 17756.4083710407
1044.4937782805))
((0 . "LWPOLYLINE") (100 . "AcDbEntity") (8 . "PLANTS") (62 . 94) (370 . 13) (100 . "AcDbPolyline") (90 . 2) (70 . 0)
(43 . 0.0) (10 17756.4083710407 765.4609728507) (10 17757.5093733102 757.7572583206))
((0 . "LWPOLYLINE") (100 . "AcDbEntity") (8 . "PLANTS") (62 . 94) (370 . 13) (100 . "AcDbPolyline") (90 . 2) (70 . 0)
(43 . 0.0) (10 17756.4083710407 765.4609728507) (10 17758.5170343122 770.3810114288))
((0 . "LWPOLYLINE") (100 . "AcDbEntity") (8 . "PLANTS") (62 . 94) (370 . 13) (100 . "AcDbPolyline") (90 . 3) (70 . 0)
(43 . 0.0) (10 17760.1809954751 4072.3981900452) (10 17766.5178733032 4061.0859728507) (10 17763.9536199095
4012.0659502262))
((0 . "LWPOLYLINE") (100 . "AcDbEntity") (8 . "PLANTS") (62 . 94) (370 . 13) (100 . "AcDbPolyline") (90 . 2) (70 . 0)
(43 . 0.0) (10 17763.9536199095 4102.5636877828) (10 17760.1809954751 4072.3981900452))
((0 . "LWPOLYLINE") (100 . "AcDbEntity") (8 . "PLANTS") (62 . 94) (370 . 13) (100 . "AcDbPolyline") (90 . 3) (70 . 0)
(43 . 0.0) (10 17763.9536199095 4102.5636877828) (10 17760.1878959276 4136.5003393665) (10 17760.1877087803
4159.4080156749))
((0 . "LWPOLYLINE") (100 . "AcDbEntity") (8 . "PLANTS") (62 . 94) (370 . 13) (100 . "AcDbPolyline") (90 . 3) (70 . 0)
(43 . 0.0) (10 17763.9536199095 4102.5636877828) (10 17786.5780542986 4111.1621040724) (10 17797.1068876082
4119.648900014))
((0 . "LWPOLYLINE") (100 . "AcDbEntity") (8 . "PLANTS") (62 . 94) (370 . 13) (100 . "AcDbPolyline") (90 . 3) (70 . 0)
(43 . 0.0) (10 17775.2658371041 3981.9004524887) (10 17774.0602941176 4004.5186651584) (10 17763.9536199095
4012.0659502262))
((0 . "LWPOLYLINE") (100 . "AcDbEntity") (8 . "PLANTS") (62 . 94) (370 . 13) (100 . "AcDbPolyline") (90 . 3) (70 . 0)
(43 . 0.0) (10 18578.4332579186 1210.407239819) (10 18585.9659502262 1225.4892533937) (10 18585.9667858994
1283.9408211195))
((0 . "LWPOLYLINE") (100 . "AcDbEntity") (8 . "PLANTS") (62 . 94) (370 . 13) (100 . "AcDbPolyline") (90 . 3) (70 . 0)
(43 . 0.0) (10 17760.3577600929 1331.1705848494) (10 17760.1878959276 1297.1351809955) (10 17763.9536199095
1285.8229638009))
((0 . "LWPOLYLINE") (100 . "AcDbEntity") (8 . "PLANTS") (62 . 94) (370 . 13) (100 . "AcDbPolyline") (90 . 3) (70 . 0)
(43 . 0.0) (10 17763.9536199095 1285.8229638009) (10 17782.8054298643 1290.6490950226) (10 17791.3331816779
1297.8124385272))
((0 . "LWPOLYLINE") (100 . "AcDbEntity") (8 . "PLANTS") (62 . 94) (370 . 13) (100 . "AcDbPolyline") (90 . 2) (70 . 0)
(43 . 0.0) (10 17771.4932126697 959.6521493213) (10 17786.5780542986 923.8320135747))
((0 . "LWPOLYLINE") (100 . "AcDbEntity") (8 . "PLANTS") (62 . 94) (370 . 13) (100 . "AcDbPolyline") (90 . 3) (70 . 0)
(43 . 0.0) (10 17771.4932126697 959.6521493213) (10 17786.5780542986 968.9255656109) (10 17812.9694570136
969.0808823529))
((0 . "LWPOLYLINE") (100 . "AcDbEntity") (8 . "PLANTS") (62 . 94) (370 . 13) (100 . "AcDbPolyline") (90 . 2) (70 . 0)
(43 . 0.0) (10 17814.8585972851 3955.5048642534) (10 17775.2658371041 3981.9004524887))
((0 . "LWPOLYLINE") (100 . "AcDbEntity") (8 . "PLANTS") (62 . 94) (370 . 13) (100 . "AcDbPolyline") (90 . 2) (70 . 0)
(43 . 0.0) (10 17775.2658371041 1127.4519230769) (10 17790.3450226244 1127.4519230769))
((0 . "LWPOLYLINE") (100 . "AcDbEntity") (8 . "PLANTS") (62 . 94) (370 . 13) (100 . "AcDbPolyline") (90 . 3) (70 . 0)
(43 . 0.0) (10 17786.5780542986 923.8320135747) (10 17782.9531674208 919.9061085973) (10 17782.9373520893
916.2895927602))
((0 . "LWPOLYLINE") (100 . "AcDbEntity") (8 . "PLANTS") (62 . 94) (370 . 13) (100 . "AcDbPolyline") (90 . 2) (70 . 0)
(43 . 0.0) (10 17786.5780542986 1059.5786199095) (10 17843.1391402715 1014.3297511312))
((0 . "LWPOLYLINE") (100 . "AcDbEntity") (8 . "PLANTS") (62 . 94) (370 . 13) (100 . "AcDbPolyline") (90 . 3) (70 . 0)
(43 . 0.0) (10 17794.1176470588 1104.8274886878) (10 17786.7244343891 1089.7426470588) (10 17786.5780542986
1059.5786199095))
((0 . "LWPOLYLINE") (100 . "AcDbEntity") (8 . "PLANTS") (62 . 94) (370 . 13) (100 . "AcDbPolyline") (90 . 2) (70 . 0)
(43 . 0.0) (10 17816.742081448 923.8320135747) (10 17786.5780542986 923.8320135747))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17816.742081448 3808.446040724 0.0) (10 17793.7147024733 3820.7919129868 0.0) (10 17784.7960141569
3852.0213113624 0.0) (10 17790.3450226244 3876.3193438914 0.0))
((0 . "LWPOLYLINE") (100 . "AcDbEntity") (8 . "PLANTS") (62 . 94) (370 . 13) (100 . "AcDbPolyline") (90 . 2) (70 . 0)
(43 . 0.0) (10 17820.5147058824 3891.4027149321) (10 17790.3450226244 3876.3193438914))
((0 . "LWPOLYLINE") (100 . "AcDbEntity") (8 . "PLANTS") (62 . 94) (370 . 13) (100 . "AcDbPolyline") (90 . 2) (70 . 0)
(43 . 0.0) (10 17794.1176470588 1104.8274886878) (10 17790.3450226244 1127.4519230769))
((0 . "LWPOLYLINE") (100 . "AcDbEntity") (8 . "PLANTS") (62 . 94) (370 . 13) (100 . "AcDbPolyline") (90 . 3) (70 . 0)
(43 . 0.0) (10 17809.2024886878 1165.1583710407) (10 17802.5535067873 1142.5339366516) (10 17790.3450226244
1127.4519230769))
((0 . "LWPOLYLINE") (100 . "AcDbEntity") (8 . "PLANTS") (62 . 94) (370 . 13) (100 . "AcDbPolyline") (90 . 2) (70 . 0)
(43 . 0.0) (10 17794.1176470588 3748.1150452489) (10 17795.4006007415 3744.3438914027))
((0 . "LWPOLYLINE") (100 . "AcDbEntity") (8 . "PLANTS") (62 . 94) (370 . 13) (100 . "AcDbPolyline") (90 . 3) (70 . 0)
(43 . 0.0) (10 17809.2024886878 3751.8849547511) (10 17797.8902714932 3751.8849547511) (10 17794.1176470588
3748.1150452489))
((0 . "LWPOLYLINE") (100 . "AcDbEntity") (8 . "PLANTS") (62 . 94) (370 . 13) (100 . "AcDbPolyline") (90 . 2) (70 . 0)
(43 . 0.0) (10 17794.1176470588 1104.8274886878) (10 17861.9909502262 1108.5972850679))
((0 . "LWPOLYLINE") (100 . "AcDbEntity") (8 . "PLANTS") (62 . 94) (370 . 13) (100 . "AcDbPolyline") (90 . 2) (70 . 0)
(43 . 0.0) (10 17816.742081448 3753.7711538462) (10 17812.9694570136 3744.3438914027))
((0 . "LWPOLYLINE") (100 . "AcDbEntity") (8 . "PLANTS") (62 . 94) (370 . 13) (100 . "AcDbPolyline") (90 . 2) (70 . 0)
(43 . 0.0) (10 17812.9694570136 3744.3438914027) (10 17809.2024886878 3751.8849547511))
((0 . "LWPOLYLINE") (100 . "AcDbEntity") (8 . "PLANTS") (62 . 94) (370 . 13) (100 . "AcDbPolyline") (90 . 2) (70 . 0)
(43 . 0.0) (10 17816.742081448 3753.7711538462) (10 17809.2024886878 3751.8849547511))
((0 . "LWPOLYLINE") (100 . "AcDbEntity") (8 . "PLANTS") (62 . 94) (370 . 13) (100 . "AcDbPolyline") (90 . 3) (70 . 0)
(43 . 0.0) (10 17821.4399174584 1265.3897999944) (10 17810.2574660634 1244.3438914027) (10 17809.2024886878
1229.2618778281))
((0 . "LWPOLYLINE") (100 . "AcDbEntity") (8 . "PLANTS") (62 . 94) (370 . 13) (100 . "AcDbPolyline") (90 . 3) (70 . 0)
(43 . 0.0) (10 17809.2024886878 1165.1583710407) (10 17814.1680995475 1191.55260181) (10 17848.8741176676
1235.8452766921))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17809.2024886878 1165.1583710407 0.0) (10 17858.2852272156 1158.3460159486 0.0) (10 17885.102404907
1226.3868336166 0.0) (10 17933.6368778281 1206.6374434389 0.0))
((0 . "LWPOLYLINE") (100 . "AcDbEntity") (8 . "PLANTS") (62 . 94) (370 . 13) (100 . "AcDbPolyline") (90 . 2) (70 . 0)
(43 . 0.0) (10 17812.9694570136 4038.4615384615) (10 17816.742081448 4087.481561086))
((0 . "LWPOLYLINE") (100 . "AcDbEntity") (8 . "PLANTS") (62 . 94) (370 . 13) (100 . "AcDbPolyline") (90 . 2) (70 . 0)
(43 . 0.0) (10 17820.5147058824 3891.4027149321) (10 17812.9694570136 3944.1926470588))
((0 . "LWPOLYLINE") (100 . "AcDbEntity") (8 . "PLANTS") (62 . 94) (370 . 13) (100 . "AcDbPolyline") (90 . 2) (70 . 0)
(43 . 0.0) (10 17814.8585972851 3955.5048642534) (10 17812.9694570136 3944.1926470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17860.8055094089 4051.0503842286 0.0) (10 17850.9682296351 4015.0614260314 0.0) (10 17804.9525880444
3999.4606380758 0.0) (10 17814.8585972851 3955.5048642534 0.0))
((0 . "LWPOLYLINE") (100 . "AcDbEntity") (8 . "PLANTS") (62 . 94) (370 . 13) (100 . "AcDbPolyline") (90 . 2) (70 . 0)
(43 . 0.0) (10 17814.8585972851 3955.5048642534) (10 17846.9061085973 3959.2760180995))
((0 . "LWPOLYLINE") (100 . "AcDbEntity") (8 . "PLANTS") (62 . 94) (370 . 13) (100 . "AcDbPolyline") (90 . 3) (70 . 0)
(43 . 0.0) (10 17816.742081448 3753.7711538462) (10 17820.217760181 3770.739479638) (10 17816.742081448 3808.446040724))
((0 . "LWPOLYLINE") (100 . "AcDbEntity") (8 . "PLANTS") (62 . 94) (370 . 13) (100 . "AcDbPolyline") (90 . 2) (70 . 0)
(43 . 0.0) (10 17816.742081448 3808.446040724) (10 17850.6787330317 3815.9883484163))
((0 . "LWPOLYLINE") (100 . "AcDbEntity") (8 . "PLANTS") (62 . 94) (370 . 13) (100 . "AcDbPolyline") (90 . 2) (70 . 0)
(43 . 0.0) (10 17824.2816742081 3755.6561085973) (10 17816.742081448 3753.7711538462))
((0 . "LWPOLYLINE") (100 . "AcDbEntity") (8 . "PLANTS") (62 . 94) (370 . 13) (100 . "AcDbPolyline") (90 . 2) (70 . 0)
(43 . 0.0) (10 17820.003280543 916.2895927602) (10 17816.742081448 923.8320135747))
((0 . "LWPOLYLINE") (100 . "AcDbEntity") (8 . "PLANTS") (62 . 94) (370 . 13) (100 . "AcDbPolyline") (90 . 3) (70 . 0)
(43 . 0.0) (10 17816.742081448 923.8320135747) (10 17828.0542986425 931.2183257919) (10 17860.1074660633 933.257918552))
((0 . "LWPOLYLINE") (100 . "AcDbEntity") (8 . "PLANTS") (62 . 94) (370 . 13) (100 . "AcDbPolyline") (90 . 2) (70 . 0)
(43 . 0.0) (10 17831.8269230769 3891.4027149321) (10 17820.5147058824 3891.4027149321))
((0 . "LWPOLYLINE") (100 . "AcDbEntity") (8 . "PLANTS") (62 . 94) (370 . 13) (100 . "AcDbPolyline") (90 . 2) (70 . 0)
(43 . 0.0) (10 17824.2816742081 3755.6561085973) (10 17850.6787330317 3755.6561085973))
((0 . "LWPOLYLINE") (100 . "AcDbEntity") (8 . "PLANTS") (62 . 94) (370 . 13) (100 . "AcDbPolyline") (90 . 2) (70 . 0)
(43 . 0.0) (10 17824.2816742081 3755.6561085973) (10 17828.0528846154 3744.3438914027))
((0 . "LWPOLYLINE") (100 . "AcDbEntity") (8 . "PLANTS") (62 . 94) (370 . 13) (100 . "AcDbPolyline") (90 . 3) (70 . 0)
(43 . 0.0) (10 18736.8042986425 512.8195701357) (10 18721.7194570136 509.0559954751) (10 18682.6955146135
509.0557237894))
((0 . "LWPOLYLINE") (100 . "AcDbEntity") (8 . "PLANTS") (62 . 94) (370 . 13) (100 . "AcDbPolyline") (90 . 2) (70 . 0)
(43 . 0.0) (10 17846.9061085973 3868.778280543) (10 17831.8269230769 3891.4027149321))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17937.4038461538 3865.0071266968 0.0) (10 17916.185892961 3897.6857051508 0.0) (10 17860.8379905829
3932.5921579892 0.0) (10 17831.8269230769 3891.4027149321 0.0))
((0 . "LWPOLYLINE") (100 . "AcDbEntity") (8 . "PLANTS") (62 . 94) (370 . 13) (100 . "AcDbPolyline") (90 . 3) (70 . 0)
(43 . 0.0) (10 17843.1391402715 1014.3297511312) (10 17843.285520362 980.3930995475) (10 17860.1074660633
933.257918552))
((0 . "LWPOLYLINE") (100 . "AcDbEntity") (8 . "PLANTS") (62 . 94) (370 . 13) (100 . "AcDbPolyline") (90 . 2) (70 . 0)
(43 . 0.0) (10 17843.1391402715 1014.3297511312) (10 17888.3880090498 1025.6419683258))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17963.8009049774 3940.4227375566 0.0) (10 17929.4706036844 3949.5479345055 0.0) (10 17871.9326647951
3923.1302638672 0.0) (10 17846.9061085973 3959.2760180995 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.6029237854)
(40 . 0.9466261195) (40 . 1) (40 . 1) (40 . 1) (40 . 1) (10 17846.9061085973 3959.2760180996 0.0) (10 17859.9413914242
3983.2125950955 0.0) (10 17915.9982319011 4002.2053937323 0.0) (10 17952.8971302991 3974.6117162491 0.0) (10
17961.8108801103 3956.9915758768 0.0) (10 17963.8009049773 3955.5048642533 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17846.9061085973 3868.778280543 0.0) (10 17861.2514874458 3871.5886617794 0.0) (10 17876.1161412812
3856.7298057617 0.0) (10 17873.3031674208 3842.3826923077 0.0))
((0 . "LWPOLYLINE") (100 . "AcDbEntity") (8 . "PLANTS") (62 . 94) (370 . 13) (100 . "AcDbPolyline") (90 . 2) (70 . 0)
(43 . 0.0) (10 17846.9061085973 3868.778280543) (10 17850.6787330317 3838.6127828054))
((0 . "LWPOLYLINE") (100 . "AcDbEntity") (8 . "PLANTS") (62 . 94) (370 . 13) (100 . "AcDbPolyline") (90 . 2) (70 . 0)
(43 . 0.0) (10 17850.6787330317 3815.9883484163) (10 17850.6787330317 3838.6127828054))
((0 . "LWPOLYLINE") (100 . "AcDbEntity") (8 . "PLANTS") (62 . 94) (370 . 13) (100 . "AcDbPolyline") (90 . 2) (70 . 0)
(43 . 0.0) (10 17850.6787330317 3838.6127828054) (10 17873.3031674208 3842.3826923077))
((0 . "LWPOLYLINE") (100 . "AcDbEntity") (8 . "PLANTS") (62 . 94) (370 . 13) (100 . "AcDbPolyline") (90 . 2) (70 . 0)
(43 . 0.0) (10 17850.6787330317 3815.9883484163) (10 17858.2183257919 3800.9049773756))
((0 . "LWPOLYLINE") (100 . "AcDbEntity") (8 . "PLANTS") (62 . 94) (370 . 13) (100 . "AcDbPolyline") (90 . 2) (70 . 0)
(43 . 0.0) (10 17857.6922511312 3744.3438914027) (10 17850.6787330317 3755.6561085973))
((0 . "LWPOLYLINE") (100 . "AcDbEntity") (8 . "PLANTS") (62 . 94) (370 . 13) (100 . "AcDbPolyline") (90 . 2) (70 . 0)
(43 . 0.0) (10 17850.6787330317 3755.6561085973) (10 17858.2183257919 3800.9049773756))
((0 . "LWPOLYLINE") (100 . "AcDbEntity") (8 . "PLANTS") (62 . 94) (370 . 13) (100 . "AcDbPolyline") (90 . 3) (70 . 0)
(43 . 0.0) (10 17880.842760181 3808.446040724) (10 17873.2962669683 3802.10260181) (10 17858.2183257919
3800.9049773756))
((0 . "LWPOLYLINE") (100 . "AcDbEntity") (8 . "PLANTS") (62 . 94) (370 . 13) (100 . "AcDbPolyline") (90 . 2) (70 . 0)
(43 . 0.0) (10 17859.2126336935 916.2895927602) (10 17860.1074660633 933.257918552))
((0 . "LWPOLYLINE") (100 . "AcDbEntity") (8 . "PLANTS") (62 . 94) (370 . 13) (100 . "AcDbPolyline") (90 . 3) (70 . 0)
(43 . 0.0) (10 18499.2477375566 935.1442307692) (10 17933.6368778281 937.7160633484) (10 17860.1074660633
933.257918552))
((0 . "LWPOLYLINE") (100 . "AcDbEntity") (8 . "PLANTS") (62 . 94) (370 . 13) (100 . "AcDbPolyline") (90 . 3) (70 . 0)
(43 . 0.0) (10 17861.9909502262 1108.5972850679) (10 17883.5590497738 1067.1182126697) (10 17888.3880090498
1025.6419683258))
((0 . "LWPOLYLINE") (100 . "AcDbEntity") (8 . "PLANTS") (62 . 94) (370 . 13) (100 . "AcDbPolyline") (90 . 3) (70 . 0)
(43 . 0.0) (10 17880.842760181 1116.1397058824) (10 17865.9168552036 1114.9410633484) (10 17861.9909502262
1108.5972850679))
((0 . "LWPOLYLINE") (100 . "AcDbEntity") (8 . "PLANTS") (62 . 94) (370 . 13) (100 . "AcDbPolyline") (90 . 2) (70 . 0)
(43 . 0.0) (10 17880.842760181 3842.3826923077) (10 17873.3031674208 3842.3826923077))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18001.5101809955 4046.00260181 0.0) (10 17961.5864130041 4070.3631806549 0.0) (10 17911.9809227254
4027.7536647732 0.0) (10 17880.842760181 4015.8371040724 0.0))
((0 . "LWPOLYLINE") (100 . "AcDbEntity") (8 . "PLANTS") (62 . 94) (370 . 13) (100 . "AcDbPolyline") (90 . 2) (70 . 0)
(43 . 0.0) (10 17892.1549773756 3842.3826923077) (10 17880.842760181 3842.3826923077))
((0 . "LWPOLYLINE") (100 . "AcDbEntity") (8 . "PLANTS") (62 . 94) (370 . 13) (100 . "AcDbPolyline") (90 . 2) (70 . 0)
(43 . 0.0) (10 17880.842760181 3842.3826923077) (10 17880.842760181 3808.446040724))
((0 . "LWPOLYLINE") (100 . "AcDbEntity") (8 . "PLANTS") (62 . 94) (370 . 13) (100 . "AcDbPolyline") (90 . 3) (70 . 0)
(43 . 0.0) (10 17933.6368778281 3819.7582579186) (10 17914.7794117647 3819.6104072398) (10 17880.842760181
3808.446040724))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17880.842760181 1116.1397058824 0.0) (10 17887.188429651 1095.7908411242 0.0) (10 17916.3364722412
1103.0944604235 0.0) (10 17929.8642533937 1101.0548642534 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17880.842760181 1116.1397058823 0.0) (10 17891.7671675178 1142.8485782279 0.0) (10 17939.5128363312
1134.0837503634 0.0) (10 17929.8642533937 1101.0548642534 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17978.8857466063 1157.6159502262 0.0) (10 17946.1385586488 1155.6782672894 0.0) (10 17914.6020567956
1189.0957210898 0.0) (10 17884.6153846154 1161.3885746606 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17971.3404977376 1021.8693438914 0.0) (10 17946.129227247 1006.328236556 0.0) (10 17913.2124960002
1013.762171818 0.0) (10 17888.3880090498 1025.6419683258 0.0))
((0 . "LWPOLYLINE") (100 . "AcDbEntity") (8 . "PLANTS") (62 . 94) (370 . 13) (100 . "AcDbPolyline") (90 . 3) (70 . 0)
(43 . 0.0) (10 18783.9366515837 3303.1674208145) (10 18748.1165158371 3306.9316742081) (10 18690.94942182
3306.9316742081))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17894.9005828319 3744.3438914027 0.0) (10 17881.0429466288 3761.3283342508 0.0) (10 17900.8873964369
3783.2213820053 0.0) (10 17918.5520361991 3774.5093891403 0.0))
((0 . "LWPOLYLINE") (100 . "AcDbEntity") (8 . "PLANTS") (62 . 94) (370 . 13) (100 . "AcDbPolyline") (90 . 3) (70 . 0)
(43 . 0.0) (10 17929.8642533937 1101.0548642534) (10 17948.7160633484 1083.4064479638) (10 17967.5735294118
1078.4304298643))
((0 . "LWPOLYLINE") (100 . "AcDbEntity") (8 . "PLANTS") (62 . 94) (370 . 13) (100 . "AcDbPolyline") (90 . 3) (70 . 0)
(43 . 0.0) (10 17971.3404977376 3763.1971719457) (10 17957.4571266968 3778.2805429864) (10 17933.6368778281
3819.7582579186))
((0 . "LWPOLYLINE") (100 . "AcDbEntity") (8 . "PLANTS") (62 . 94) (370 . 13) (100 . "AcDbPolyline") (90 . 3) (70 . 0)
(43 . 0.0) (10 17937.4038461538 3865.0071266968) (10 17931.0600678733 3846.1538461538) (10 17933.6368778281
3819.7582579186))
((0 . "LWPOLYLINE") (100 . "AcDbEntity") (8 . "PLANTS") (62 . 94) (370 . 13) (100 . "AcDbPolyline") (90 . 2) (70 . 0)
(43 . 0.0) (10 18129.7115384615 4091.2514705882) (10 18129.7116513785 4100.0508673384))
((0 . "LWPOLYLINE") (100 . "AcDbEntity") (8 . "PLANTS") (62 . 94) (370 . 13) (100 . "AcDbPolyline") (90 . 3) (70 . 0)
(43 . 0.0) (10 17937.4038461538 3865.0071266968) (10 17986.4253393665 3865.1621040724) (10 18001.5101809955
3872.5494343891))
((0 . "LWPOLYLINE") (100 . "AcDbEntity") (8 . "PLANTS") (62 . 94) (370 . 13) (100 . "AcDbPolyline") (90 . 2) (70 . 0)
(43 . 0.0) (10 18133.4841628959 1251.8863122172) (10 18133.4841628959 1270.7390648567))
((0 . "LWPOLYLINE") (100 . "AcDbEntity") (8 . "PLANTS") (62 . 94) (370 . 13) (100 . "AcDbPolyline") (90 . 2) (70 . 0)
(43 . 0.0) (10 18634.9943438914 886.1227375566) (10 18623.5487023062 885.0008346353))
((0 . "LWPOLYLINE") (100 . "AcDbEntity") (8 . "PLANTS") (62 . 94) (370 . 13) (100 . "AcDbPolyline") (90 . 3) (70 . 0)
(43 . 0.0) (10 18635.2614169541 754.1478506787) (10 18638.7613122172 754.1478506787) (10 18650.0735294118
754.1478506787))
((0 . "LWPOLYLINE") (100 . "AcDbEntity") (8 . "PLANTS") (62 . 94) (370 . 13) (100 . "AcDbPolyline") (90 . 3) (70 . 0)
(43 . 0.0) (10 17997.7375565611 4027.149321267) (10 17990.1895927602 4023.5265837104) (10 17956.2613122172
4023.3781674208))
((0 . "LWPOLYLINE") (100 . "AcDbEntity") (8 . "PLANTS") (62 . 94) (370 . 13) (100 . "AcDbPolyline") (90 . 2) (70 . 0)
(43 . 0.0) (10 17963.8009049774 3940.4227375566) (10 17963.8009049774 3955.5048642534))
((0 . "LWPOLYLINE") (100 . "AcDbEntity") (8 . "PLANTS") (62 . 94) (370 . 13) (100 . "AcDbPolyline") (90 . 3) (70 . 0)
(43 . 0.0) (10 18016.5893665158 3955.5048642534) (10 17986.4253393665 3963.0340497738) (10 17963.8009049774
3955.5048642534))
((0 . "LWPOLYLINE") (100 . "AcDbEntity") (8 . "PLANTS") (62 . 94) (370 . 13) (100 . "AcDbPolyline") (90 . 3) (70 . 0)
(43 . 0.0) (10 17963.8009049774 3940.4227375566) (10 17975.1200226244 3925.4874434389) (10 17997.7375565611
3914.0271493213))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6310530006) (40
. 1) (40 . 1) (40 . 1) (40 . 1) (10 18020.3619909503 1221.7194570136 0.0) (10 18008.6352004802 1241.3547745611 0.0) (10
17980.9021727559 1239.15757425 0.0) (10 17969.6864491622 1212.3978446079 0.0) (10 17963.8009049775 1206.6374434388 0.0))
((0 . "LWPOLYLINE") (100 . "AcDbEntity") (8 . "PLANTS") (62 . 94) (370 . 13) (100 . "AcDbPolyline") (90 . 3) (70 . 0)
(43 . 0.0) (10 17971.3404977376 1021.8693438914) (10 17967.7199095023 1033.181561086) (10 17967.5735294118
1078.4304298643))
((0 . "LWPOLYLINE") (100 . "AcDbEntity") (8 . "PLANTS") (62 . 94) (370 . 13) (100 . "AcDbPolyline") (90 . 3) (70 . 0)
(43 . 0.0) (10 18024.1346153846 1082.2030542986) (10 17982.6527149321 1082.054638009) (10 17967.5735294118
1078.4304298643))
((0 . "LWPOLYLINE") (100 . "AcDbEntity") (8 . "PLANTS") (62 . 94) (370 . 13) (100 . "AcDbPolyline") (90 . 3) (70 . 0)
(43 . 0.0) (10 17971.3404977376 3763.1971719457) (10 17972.3983031674 3748.1150452489) (10 17974.1333586241
3744.3438914027))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17971.3404977376 3763.1971719457 0.0) (10 18183.7594268412 3763.1982962805 0.0) (10 18396.1783559578
3763.1974653415 0.0) (10 18608.5972850679 3763.1976244344 0.0))
((0 . "LWPOLYLINE") (100 . "AcDbEntity") (8 . "PLANTS") (62 . 94) (370 . 13) (100 . "AcDbPolyline") (90 . 2) (70 . 0)
(43 . 0.0) (10 17971.3404977376 1021.8693438914) (10 18009.0497737557 1006.7873303167))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 17978.8857466063 1157.6159502262 0.0) (10 17994.5341452421 1134.3463631182 0.0) (10 18023.3768151644
1122.1799285099 0.0) (10 18050.5260180996 1127.4519230769 0.0))
((0 . "LWPOLYLINE") (100 . "AcDbEntity") (8 . "PLANTS") (62 . 94) (370 . 13) (100 . "AcDbPolyline") (90 . 2) (70 . 0)
(43 . 0.0) (10 17978.8857466063 1157.6159502262) (10 17986.4253393665 1168.9281674208))
((0 . "LWPOLYLINE") (100 . "AcDbEntity") (8 . "PLANTS") (62 . 94) (370 . 13) (100 . "AcDbPolyline") (90 . 2) (70 . 0)
(43 . 0.0) (10 17997.7375565611 3914.0271493213) (10 18001.5101809955 3872.5494343891))
((0 . "LWPOLYLINE") (100 . "AcDbEntity") (8 . "PLANTS") (62 . 94) (370 . 13) (100 . "AcDbPolyline") (90 . 3) (70 . 0)
(43 . 0.0) (10 18016.5893665158 3955.5048642534) (10 18011.6168552036 3929.110520362) (10 17997.7375565611
3914.0271493213))
((0 . "LWPOLYLINE") (100 . "AcDbEntity") (8 . "PLANTS") (62 . 94) (370 . 13) (100 . "AcDbPolyline") (90 . 2) (70 . 0)
(43 . 0.0) (10 18027.9015837104 1195.3252262443) (10 17997.7375565611 1191.55260181))
((0 . "LWPOLYLINE") (100 . "AcDbEntity") (8 . "PLANTS") (62 . 94) (370 . 13) (100 . "AcDbPolyline") (90 . 3) (70 . 0)
(43 . 0.0) (10 18001.5101809955 3872.5494343891) (10 18031.6742081448 3865.1555429864) (10 18073.1504524887
3865.0071266968))
((0 . "LWPOLYLINE") (100 . "AcDbEntity") (8 . "PLANTS") (62 . 94) (370 . 13) (100 . "AcDbPolyline") (90 . 3) (70 . 0)
(43 . 0.0) (10 18645.5348403853 3472.9787375787) (10 18646.306561086 3473.0053167421) (10 18657.6187782805
3480.3924208145))
((0 . "LWPOLYLINE") (100 . "AcDbEntity") (8 . "PLANTS") (62 . 94) (370 . 13) (100 . "AcDbPolyline") (90 . 2) (70 . 0)
(43 . 0.0) (10 18016.5893665158 972.850678733) (10 18009.0497737557 1006.7873303167))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18073.1504524887 1025.6419683258 0.0) (10 18043.2649239465 1038.5520048354 0.0) (10 18036.673960448
999.9524172516 0.0) (10 18009.0497737557 1006.7873303167 0.0))
((0 . "LWPOLYLINE") (100 . "AcDbEntity") (8 . "PLANTS") (62 . 94) (370 . 13) (100 . "AcDbPolyline") (90 . 3) (70 . 0)
(43 . 0.0) (10 18016.5893665158 3955.5048642534) (10 18046.7590497738 3956.5615384615) (10 18061.8382352941
3966.817081448))
((0 . "LWPOLYLINE") (100 . "AcDbEntity") (8 . "PLANTS") (62 . 94) (370 . 13) (100 . "AcDbPolyline") (90 . 3) (70 . 0)
(43 . 0.0) (10 18027.9015837104 1195.3252262443) (10 18045.7012443439 1168.9281674208) (10 18050.5260180996
1127.4519230769))
((0 . "LWPOLYLINE") (100 . "AcDbEntity") (8 . "PLANTS") (62 . 94) (370 . 13) (100 . "AcDbPolyline") (90 . 2) (70 . 0)
(43 . 0.0) (10 18031.6742081448 1202.8648190045) (10 18027.9015837104 1195.3252262443))
((0 . "LWPOLYLINE") (100 . "AcDbEntity") (8 . "PLANTS") (62 . 94) (370 . 13) (100 . "AcDbPolyline") (90 . 2) (70 . 0)
(43 . 0.0) (10 18031.6742081448 4004.5248868778) (10 18039.213800905 4004.5248868778))
((0 . "LWPOLYLINE") (100 . "AcDbEntity") (8 . "PLANTS") (62 . 94) (370 . 13) (100 . "AcDbPolyline") (90 . 2) (70 . 0)
(43 . 0.0) (10 18035.4468325792 3808.446040724) (10 18042.9864253394 3804.6761312217))
((0 . "LWPOLYLINE") (100 . "AcDbEntity") (8 . "PLANTS") (62 . 94) (370 . 13) (100 . "AcDbPolyline") (90 . 2) (70 . 0)
(43 . 0.0) (10 18061.8382352941 3966.817081448) (10 18039.213800905 4004.5248868778))
((0 . "LWPOLYLINE") (100 . "AcDbEntity") (8 . "PLANTS") (62 . 94) (370 . 13) (100 . "AcDbPolyline") (90 . 2) (70 . 0)
(43 . 0.0) (10 18039.213800905 4004.5248868778) (10 18050.5260180996 4027.149321267))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18042.9864253394 4087.481561086 0.0) (10 18024.3876904138 4055.2163273252 0.0) (10 18119.281498928
4059.3342446269 0.0) (10 18099.5475113122 4019.6082579186 0.0))
((0 . "LWPOLYLINE") (100 . "AcDbEntity") (8 . "PLANTS") (62 . 94) (370 . 13) (100 . "AcDbPolyline") (90 . 2) (70 . 0)
(43 . 0.0) (10 18046.7590497738 3921.5682126697) (10 18058.0712669683 3925.3393665158))
((0 . "LWPOLYLINE") (100 . "AcDbEntity") (8 . "PLANTS") (62 . 94) (370 . 13) (100 . "AcDbPolyline") (90 . 2) (70 . 0)
(43 . 0.0) (10 18076.9230769231 1119.9095022624) (10 18050.5260180996 1127.4519230769))
((0 . "LWPOLYLINE") (100 . "AcDbEntity") (8 . "PLANTS") (62 . 94) (370 . 13) (100 . "AcDbPolyline") (90 . 3) (70 . 0)
(43 . 0.0) (10 18073.1504524887 1195.3252262443) (10 18059.1262443439 1217.9496606335) (10 18054.2986425339
1266.9683257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18133.4841628959 1251.8863122172 0.0) (10 18107.7147897998 1240.5493265047 0.0) (10 18084.2293621797
1265.3478550587 0.0) (10 18080.0338172854 1288.5558467269 0.0))
((0 . "LWPOLYLINE") (100 . "AcDbEntity") (8 . "PLANTS") (62 . 94) (370 . 13) (100 . "AcDbPolyline") (90 . 2) (70 . 0)
(43 . 0.0) (10 18061.8382352941 3966.817081448) (10 18080.6957013575 3966.817081448))
((0 . "LWPOLYLINE") (100 . "AcDbEntity") (8 . "PLANTS") (62 . 94) (370 . 13) (100 . "AcDbPolyline") (90 . 2) (70 . 0)
(43 . 0.0) (10 18665.1583710407 3582.2021493213) (10 18635.2614169541 3582.2021493213))
((0 . "LWPOLYLINE") (100 . "AcDbEntity") (8 . "PLANTS") (62 . 94) (370 . 13) (100 . "AcDbPolyline") (90 . 3) (70 . 0)
(43 . 0.0) (10 18129.7115384615 4091.2514705882) (10 18099.5475113122 4092.4562217195) (10 18074.9729256194
4117.0312215697))
((0 . "LWPOLYLINE") (100 . "AcDbEntity") (8 . "PLANTS") (62 . 94) (370 . 13) (100 . "AcDbPolyline") (90 . 3) (70 . 0)
(43 . 0.0) (10 18114.6323529412 3838.6127828054) (10 18099.5475113122 3843.4331447964) (10 18073.1504524887
3865.0071266968))
((0 . "LWPOLYLINE") (100 . "AcDbEntity") (8 . "PLANTS") (62 . 94) (370 . 13) (100 . "AcDbPolyline") (90 . 3) (70 . 0)
(43 . 0.0) (10 18125.9445701357 3887.631561086) (10 18084.4626696833 3878.8859728507) (10 18073.1504524887
3865.0071266968))
((0 . "LWPOLYLINE") (100 . "AcDbEntity") (8 . "PLANTS") (62 . 94) (370 . 13) (100 . "AcDbPolyline") (90 . 3) (70 . 0)
(43 . 0.0) (10 18073.1504524887 1195.3252262443) (10 18090.9501131222 1157.6159502262) (10 18092.007918552
1134.9915158371))
((0 . "LWPOLYLINE") (100 . "AcDbEntity") (8 . "PLANTS") (62 . 94) (370 . 13) (100 . "AcDbPolyline") (90 . 3) (70 . 0)
(43 . 0.0) (10 18129.7115384615 1191.55260181) (10 18084.4626696833 1197.8970588235) (10 18073.1504524887
1195.3252262443))
((0 . "LWPOLYLINE") (100 . "AcDbEntity") (8 . "PLANTS") (62 . 94) (370 . 13) (100 . "AcDbPolyline") (90 . 3) (70 . 0)
(43 . 0.0) (10 18133.4841628959 1018.0995475113) (10 18084.4626696833 1018.2541855204) (10 18073.1504524887
1025.6419683258))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18107.0871040724 1067.1182126697 0.0) (10 18097.8403340341 1047.3674873927 0.0) (10 18063.0106197222
1061.2838917481 0.0) (10 18073.1504524887 1025.6419683258 0.0))
((0 . "LWPOLYLINE") (100 . "AcDbEntity") (8 . "PLANTS") (62 . 94) (370 . 13) (100 . "AcDbPolyline") (90 . 3) (70 . 0)
(43 . 0.0) (10 18672.6979638009 3529.4117647059) (10 18665.1514705882 3533.0345022624) (10 18639.6519147886
3533.1520563268))
((0 . "LWPOLYLINE") (100 . "AcDbEntity") (8 . "PLANTS") (62 . 94) (370 . 13) (100 . "AcDbPolyline") (90 . 3) (70 . 0)
(43 . 0.0) (10 18076.9230769231 1119.9095022624) (10 18096.8326923077 1078.4304298643) (10 18107.0871040724
1067.1182126697))
((0 . "LWPOLYLINE") (100 . "AcDbEntity") (8 . "PLANTS") (62 . 94) (370 . 13) (100 . "AcDbPolyline") (90 . 2) (70 . 0)
(43 . 0.0) (10 18076.9230769231 1119.9095022624) (10 18092.007918552 1134.9915158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18080.6957013575 3966.817081448 0.0) (10 18071.4564179345 3941.2672444975 0.0) (10 18115.1199342646
3935.3135143948 0.0) (10 18125.9445701357 3932.8804298643 0.0))
((0 . "LWPOLYLINE") (100 . "AcDbEntity") (8 . "PLANTS") (62 . 94) (370 . 13) (100 . "AcDbPolyline") (90 . 3) (70 . 0)
(43 . 0.0) (10 18131.600678733 3995.0976244344) (10 18099.5475113122 3988.2376696833) (10 18080.6957013575
3966.817081448))
((0 . "LWPOLYLINE") (100 . "AcDbEntity") (8 . "PLANTS") (62 . 94) (370 . 13) (100 . "AcDbPolyline") (90 . 2) (70 . 0)
(43 . 0.0) (10 18092.007918552 1134.9915158371) (10 18125.9445701357 1134.9915158371))
((0 . "LWPOLYLINE") (100 . "AcDbEntity") (8 . "PLANTS") (62 . 94) (370 . 13) (100 . "AcDbPolyline") (90 . 2) (70 . 0)
(43 . 0.0) (10 18107.0871040724 1067.1182126697) (10 18125.9445701357 1067.1182126697))
((0 . "LWPOLYLINE") (100 . "AcDbEntity") (8 . "PLANTS") (62 . 94) (370 . 13) (100 . "AcDbPolyline") (90 . 3) (70 . 0)
(43 . 0.0) (10 18122.1719457014 3808.446040724) (10 18114.7856334842 3819.7589366516) (10 18114.6323529412
3838.6127828054))
((0 . "LWPOLYLINE") (100 . "AcDbEntity") (8 . "PLANTS") (62 . 94) (370 . 13) (100 . "AcDbPolyline") (90 . 2) (70 . 0)
(43 . 0.0) (10 18141.0237556561 3853.6949095023) (10 18114.6323529412 3838.6127828054))
((0 . "LWPOLYLINE") (100 . "AcDbEntity") (8 . "PLANTS") (62 . 94) (370 . 13) (100 . "AcDbPolyline") (90 . 2) (70 . 0)
(43 . 0.0) (10 18125.9445701357 3925.3393665158) (10 18125.9445701357 3932.8804298643))
((0 . "LWPOLYLINE") (100 . "AcDbEntity") (8 . "PLANTS") (62 . 94) (370 . 13) (100 . "AcDbPolyline") (90 . 3) (70 . 0)
(43 . 0.0) (10 18137.2567873303 3966.817081448) (10 18132.2883484163 3940.428959276) (10 18125.9445701357
3932.8804298643))
((0 . "LWPOLYLINE") (100 . "AcDbEntity") (8 . "PLANTS") (62 . 94) (370 . 13) (100 . "AcDbPolyline") (90 . 2) (70 . 0)
(43 . 0.0) (10 18171.193438914 3925.3393665158) (10 18125.9445701357 3925.3393665158))
((0 . "LWPOLYLINE") (100 . "AcDbEntity") (8 . "PLANTS") (62 . 94) (370 . 13) (100 . "AcDbPolyline") (90 . 2) (70 . 0)
(43 . 0.0) (10 18125.9445701357 3887.631561086) (10 18125.9445701357 3925.3393665158))
((0 . "LWPOLYLINE") (100 . "AcDbEntity") (8 . "PLANTS") (62 . 94) (370 . 13) (100 . "AcDbPolyline") (90 . 2) (70 . 0)
(43 . 0.0) (10 18137.2567873303 3887.631561086) (10 18125.9445701357 3887.631561086))
((0 . "LWPOLYLINE") (100 . "AcDbEntity") (8 . "PLANTS") (62 . 94) (370 . 13) (100 . "AcDbPolyline") (90 . 2) (70 . 0)
(43 . 0.0) (10 18137.2567873303 1112.367081448) (10 18125.9445701357 1134.9915158371))
((0 . "LWPOLYLINE") (100 . "AcDbEntity") (8 . "PLANTS") (62 . 94) (370 . 13) (100 . "AcDbPolyline") (90 . 3) (70 . 0)
(43 . 0.0) (10 18129.7115384615 1191.55260181) (10 18137.0937782805 1165.1583710407) (10 18125.9445701357
1134.9915158371))
((0 . "LWPOLYLINE") (100 . "AcDbEntity") (8 . "PLANTS") (62 . 94) (370 . 13) (100 . "AcDbPolyline") (90 . 2) (70 . 0)
(43 . 0.0) (10 18125.9445701357 1067.1182126697) (10 18133.4841628959 1063.3484162896))
((0 . "LWPOLYLINE") (100 . "AcDbEntity") (8 . "PLANTS") (62 . 94) (370 . 13) (100 . "AcDbPolyline") (90 . 3) (70 . 0)
(43 . 0.0) (10 18137.2567873303 1112.367081448) (10 18136.1989819005 1085.9728506787) (10 18125.9445701357
1067.1182126697))
((0 . "LWPOLYLINE") (100 . "AcDbEntity") (8 . "PLANTS") (62 . 94) (370 . 13) (100 . "AcDbPolyline") (90 . 2) (70 . 0)
(43 . 0.0) (10 18129.7115384615 4091.2514705882) (10 18129.7115384615 4061.0859728507))
((0 . "LWPOLYLINE") (100 . "AcDbEntity") (8 . "PLANTS") (62 . 94) (370 . 13) (100 . "AcDbPolyline") (90 . 2) (70 . 0)
(43 . 0.0) (10 18129.7115384615 4061.0859728507) (10 18167.4208144796 4057.3148190045))
((0 . "LWPOLYLINE") (100 . "AcDbEntity") (8 . "PLANTS") (62 . 94) (370 . 13) (100 . "AcDbPolyline") (90 . 2) (70 . 0)
(43 . 0.0) (10 18131.600678733 3995.0976244344) (10 18129.7115384615 4061.0859728507))
((0 . "LWPOLYLINE") (100 . "AcDbEntity") (8 . "PLANTS") (62 . 94) (370 . 13) (100 . "AcDbPolyline") (90 . 3) (70 . 0)
(43 . 0.0) (10 18133.4841628959 1251.8863122172) (10 18133.4841628959 1225.4892533937) (10 18129.7115384615
1191.55260181))
((0 . "LWPOLYLINE") (100 . "AcDbEntity") (8 . "PLANTS") (62 . 94) (370 . 13) (100 . "AcDbPolyline") (90 . 2) (70 . 0)
(43 . 0.0) (10 18131.600678733 3995.0976244344) (10 18137.2567873303 3966.817081448))
((0 . "LWPOLYLINE") (100 . "AcDbEntity") (8 . "PLANTS") (62 . 94) (370 . 13) (100 . "AcDbPolyline") (90 . 2) (70 . 0)
(43 . 0.0) (10 18131.600678733 3995.0976244344) (10 18167.4208144796 3996.9838235294))
((0 . "LWPOLYLINE") (100 . "AcDbEntity") (8 . "PLANTS") (62 . 94) (370 . 13) (100 . "AcDbPolyline") (90 . 2) (70 . 0)
(43 . 0.0) (10 18159.8812217195 1063.3484162896) (10 18133.4841628959 1063.3484162896))
((0 . "LWPOLYLINE") (100 . "AcDbEntity") (8 . "PLANTS") (62 . 94) (370 . 13) (100 . "AcDbPolyline") (90 . 2) (70 . 0)
(43 . 0.0) (10 18133.4841628959 1018.0995475113) (10 18133.4841628959 1063.3484162896))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18220.2092760181 1018.0995475113 0.0) (10 18192.4238286849 1009.9149283577 0.0) (10 18160.8118684219
1007.4473866232 0.0) (10 18133.4841628959 1018.0995475113 0.0))
((0 . "LWPOLYLINE") (100 . "AcDbEntity") (8 . "PLANTS") (62 . 94) (370 . 13) (100 . "AcDbPolyline") (90 . 3) (70 . 0)
(43 . 0.0) (10 18137.2567873303 3966.817081448) (10 18167.2730769231 3968.0218325792) (10 18178.7330316742
3981.9004524887))
((0 . "LWPOLYLINE") (100 . "AcDbEntity") (8 . "PLANTS") (62 . 94) (370 . 13) (100 . "AcDbPolyline") (90 . 2) (70 . 0)
(43 . 0.0) (10 18137.2567873303 3887.631561086) (10 18141.0237556561 3853.6949095023))
((0 . "LWPOLYLINE") (100 . "AcDbEntity") (8 . "PLANTS") (62 . 94) (370 . 13) (100 . "AcDbPolyline") (90 . 3) (70 . 0)
(43 . 0.0) (10 18137.2567873303 3887.631561086) (10 18174.9604072398 3892.6069004525) (10 18186.2726244344
3902.7149321267))
((0 . "LWPOLYLINE") (100 . "AcDbEntity") (8 . "PLANTS") (62 . 94) (370 . 13) (100 . "AcDbPolyline") (90 . 2) (70 . 0)
(43 . 0.0) (10 18137.2567873303 1112.367081448) (10 18171.1915158371 1116.1397058824))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18212.6696832579 3861.2372171946 0.0) (10 18194.0865750694 3843.214367092 0.0) (10 18163.5508722219
3841.8486103523 0.0) (10 18141.0237556561 3853.6949095023 0.0))
((0 . "LWPOLYLINE") (100 . "AcDbEntity") (8 . "PLANTS") (62 . 94) (370 . 13) (100 . "AcDbPolyline") (90 . 3) (70 . 0)
(43 . 0.0) (10 18159.8812217195 1063.3484162896) (10 18167.4277149321 1059.725678733) (10 18205.1300904977
1059.5786199095))
((0 . "LWPOLYLINE") (100 . "AcDbEntity") (8 . "PLANTS") (62 . 94) (370 . 13) (100 . "AcDbPolyline") (90 . 3) (70 . 0)
(43 . 0.0) (10 18159.8812217195 1063.3484162896) (10 18171.1915158371 1078.4304298643) (10 18171.1915158371
1093.5152714932))
((0 . "LWPOLYLINE") (100 . "AcDbEntity") (8 . "PLANTS") (62 . 94) (370 . 13) (100 . "AcDbPolyline") (90 . 2) (70 . 0)
(43 . 0.0) (10 18174.9604072398 4038.4615384615) (10 18167.4208144796 4057.3148190045))
((0 . "LWPOLYLINE") (100 . "AcDbEntity") (8 . "PLANTS") (62 . 94) (370 . 13) (100 . "AcDbPolyline") (90 . 2) (70 . 0)
(43 . 0.0) (10 18171.193438914 4068.6270361991) (10 18167.4208144796 4057.3148190045))
((0 . "LWPOLYLINE") (100 . "AcDbEntity") (8 . "PLANTS") (62 . 94) (370 . 13) (100 . "AcDbPolyline") (90 . 2) (70 . 0)
(43 . 0.0) (10 18167.4208144796 3996.9838235294) (10 18178.7330316742 3981.9004524887))
((0 . "LWPOLYLINE") (100 . "AcDbEntity") (8 . "PLANTS") (62 . 94) (370 . 13) (100 . "AcDbPolyline") (90 . 2) (70 . 0)
(43 . 0.0) (10 18171.193438914 4019.6082579186) (10 18167.4208144796 3996.9838235294))
((0 . "LWPOLYLINE") (100 . "AcDbEntity") (8 . "PLANTS") (62 . 94) (370 . 13) (100 . "AcDbPolyline") (90 . 2) (70 . 0)
(43 . 0.0) (10 18171.1915158371 1217.9496606335) (10 18171.1915158371 1199.0950226244))
((0 . "LWPOLYLINE") (100 . "AcDbEntity") (8 . "PLANTS") (62 . 94) (370 . 13) (100 . "AcDbPolyline") (90 . 2) (70 . 0)
(43 . 0.0) (10 18205.1300904977 1199.0950226244) (10 18171.1915158371 1199.0950226244))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18171.1915158371 1199.0950226244 0.0) (10 18171.1915158371 1171.4432503771 0.0) (10 18171.1915158371
1143.7914781297 0.0) (10 18171.1915158371 1116.1397058824 0.0))
((0 . "LWPOLYLINE") (100 . "AcDbEntity") (8 . "PLANTS") (62 . 94) (370 . 13) (100 . "AcDbPolyline") (90 . 2) (70 . 0)
(43 . 0.0) (10 18171.1915158371 1093.5152714932) (10 18171.1915158371 1116.1397058824))
((0 . "LWPOLYLINE") (100 . "AcDbEntity") (8 . "PLANTS") (62 . 94) (370 . 13) (100 . "AcDbPolyline") (90 . 2) (70 . 0)
(43 . 0.0) (10 18212.6696832579 1093.5152714932) (10 18171.1915158371 1093.5152714932))
((0 . "LWPOLYLINE") (100 . "AcDbEntity") (8 . "PLANTS") (62 . 94) (370 . 13) (100 . "AcDbPolyline") (90 . 2) (70 . 0)
(43 . 0.0) (10 18171.193438914 3951.7349547511) (10 18171.193438914 3925.3393665158))
((0 . "LWPOLYLINE") (100 . "AcDbEntity") (8 . "PLANTS") (62 . 94) (370 . 13) (100 . "AcDbPolyline") (90 . 2) (70 . 0)
(43 . 0.0) (10 18186.2726244344 3902.7149321267) (10 18171.193438914 3925.3393665158))
((0 . "LWPOLYLINE") (100 . "AcDbEntity") (8 . "PLANTS") (62 . 94) (370 . 13) (100 . "AcDbPolyline") (90 . 2) (70 . 0)
(43 . 0.0) (10 18208.8970588235 3981.9004524887) (10 18178.7330316742 3981.9004524887))
((0 . "LWPOLYLINE") (100 . "AcDbEntity") (8 . "PLANTS") (62 . 94) (370 . 13) (100 . "AcDbPolyline") (90 . 2) (70 . 0)
(43 . 0.0) (10 18197.584841629 3902.7149321267) (10 18186.2726244344 3902.7149321267))
((0 . "LWPOLYLINE") (100 . "AcDbEntity") (8 . "PLANTS") (62 . 94) (370 . 13) (100 . "AcDbPolyline") (90 . 2) (70 . 0)
(43 . 0.0) (10 18197.584841629 3902.7149321267) (10 18212.6696832579 3872.5494343891))
((0 . "LWPOLYLINE") (100 . "AcDbEntity") (8 . "PLANTS") (62 . 94) (370 . 13) (100 . "AcDbPolyline") (90 . 3) (70 . 0)
(43 . 0.0) (10 18212.6696832579 3929.110520362) (10 18211.4654977376 3921.5619909502) (10 18197.584841629
3902.7149321267))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5052788146)
(40 . 0.6927639288) (40 . 1) (40 . 1) (40 . 1) (40 . 1) (10 18205.1300904978 1199.0950226244 0.0) (10 18212.1280663523
1182.2022657507 0.0) (10 18205.0584783202 1157.7041410884 0.0) (10 18211.1962311698 1122.7829944525 0.0) (10
18213.7962402502 1105.3386815685 0.0) (10 18220.209276018 1097.2850678733 0.0))
((0 . "LWPOLYLINE") (100 . "AcDbEntity") (8 . "PLANTS") (62 . 94) (370 . 13) (100 . "AcDbPolyline") (90 . 2) (70 . 0)
(43 . 0.0) (10 18533.1843891403 1263.1985294118) (10 18533.1159622664 1320.2757623672))
((0 . "LWPOLYLINE") (100 . "AcDbEntity") (8 . "PLANTS") (62 . 94) (370 . 13) (100 . "AcDbPolyline") (90 . 3) (70 . 0)
(43 . 0.0) (10 18208.8231706141 1245.626062284) (10 18208.8929864253 1214.1770361991) (10 18205.1300904977
1199.0950226244))
((0 . "LWPOLYLINE") (100 . "AcDbEntity") (8 . "PLANTS") (62 . 94) (370 . 13) (100 . "AcDbPolyline") (90 . 3) (70 . 0)
(43 . 0.0) (10 18220.2092760181 1018.0995475113) (10 18211.4794117647 1052.0292986425) (10 18205.1300904977
1059.5786199095))
((0 . "LWPOLYLINE") (100 . "AcDbEntity") (8 . "PLANTS") (62 . 94) (370 . 13) (100 . "AcDbPolyline") (90 . 2) (70 . 0)
(43 . 0.0) (10 18212.6696832579 1093.5152714932) (10 18205.1300904977 1059.5786199095))
((0 . "LWPOLYLINE") (100 . "AcDbEntity") (8 . "PLANTS") (62 . 94) (370 . 13) (100 . "AcDbPolyline") (90 . 3) (70 . 0)
(43 . 0.0) (10 18212.6696832579 3929.110520362) (10 18212.5219457014 3970.5882352941) (10 18208.8970588235
3981.9004524887))
((0 . "LWPOLYLINE") (100 . "AcDbEntity") (8 . "PLANTS") (62 . 94) (370 . 13) (100 . "AcDbPolyline") (90 . 2) (70 . 0)
(43 . 0.0) (10 18208.8989819005 3993.2126696833) (10 18208.8970588235 3981.9004524887))
((0 . "LWPOLYLINE") (100 . "AcDbEntity") (8 . "PLANTS") (62 . 94) (370 . 13) (100 . "AcDbPolyline") (90 . 3) (70 . 0)
(43 . 0.0) (10 18208.8989819005 3993.2126696833) (10 18208.8989819005 4008.296040724) (10 18208.9726741465
4073.6305264157))
((0 . "LWPOLYLINE") (100 . "AcDbEntity") (8 . "PLANTS") (62 . 94) (370 . 13) (100 . "AcDbPolyline") (90 . 2) (70 . 0)
(43 . 0.0) (10 18208.8989819005 3993.2126696833) (10 18246.6063348416 4000.7537330317))
((0 . "LWPOLYLINE") (100 . "AcDbEntity") (8 . "PLANTS") (62 . 94) (370 . 13) (100 . "AcDbPolyline") (90 . 3) (70 . 0)
(43 . 0.0) (10 18212.6696832579 3929.110520362) (10 18246.6063348416 3933.0354072398) (10 18265.4581447964
3940.4227375566))
((0 . "LWPOLYLINE") (100 . "AcDbEntity") (8 . "PLANTS") (62 . 94) (370 . 13) (100 . "AcDbPolyline") (90 . 2) (70 . 0)
(43 . 0.0) (10 18212.6696832579 3861.2372171946) (10 18212.6696832579 3872.5494343891))
((0 . "LWPOLYLINE") (100 . "AcDbEntity") (8 . "PLANTS") (62 . 94) (370 . 13) (100 . "AcDbPolyline") (90 . 3) (70 . 0)
(43 . 0.0) (10 18314.4796380091 3880.0904977376) (10 18231.5214932127 3879.9424208145) (10 18212.6696832579
3872.5494343891))
((0 . "LWPOLYLINE") (100 . "AcDbEntity") (8 . "PLANTS") (62 . 94) (370 . 13) (100 . "AcDbPolyline") (90 . 3) (70 . 0)
(43 . 0.0) (10 18314.4796380091 3849.925) (10 18227.7545248869 3853.8498868778) (10 18212.6696832579 3861.2372171946))
((0 . "LWPOLYLINE") (100 . "AcDbEntity") (8 . "PLANTS") (62 . 94) (370 . 13) (100 . "AcDbPolyline") (90 . 2) (70 . 0)
(43 . 0.0) (10 18212.6696832579 1093.5152714932) (10 18220.2092760181 1097.2850678733))
((0 . "LWPOLYLINE") (100 . "AcDbEntity") (8 . "PLANTS") (62 . 94) (370 . 13) (100 . "AcDbPolyline") (90 . 2) (70 . 0)
(43 . 0.0) (10 18227.7545248869 1097.2850678733) (10 18220.2092760181 1097.2850678733))
((0 . "LWPOLYLINE") (100 . "AcDbEntity") (8 . "PLANTS") (62 . 94) (370 . 13) (100 . "AcDbPolyline") (90 . 2) (70 . 0)
(43 . 0.0) (10 18220.2092760181 1018.0995475113) (10 18261.6911764706 1018.0995475113))
((0 . "LWPOLYLINE") (100 . "AcDbEntity") (8 . "PLANTS") (62 . 94) (370 . 13) (100 . "AcDbPolyline") (90 . 3) (70 . 0)
(43 . 0.0) (10 18227.7545248869 1097.2850678733) (10 18239.0667420814 1086.1274886878) (10 18288.0825791855
1089.7426470588))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.4220122877)
(40 . 0.5567667464) (40 . 0.7100300072) (40 . 1) (40 . 1) (40 . 1) (40 . 1) (10 18227.7545248869 1097.2850678733 0.0)
(10 18256.9956816476 1099.175696666 0.0) (10 18259.1952235203 1147.8519648837 0.0) (10 18291.8254718866 1167.828654682
0.0) (10 18326.3958206686 1172.3611367793 0.0) (10 18349.1622227851 1185.7099821847 0.0) (10 18363.5011312217
1168.9281674208 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18329.564479638 1029.4117647059 0.0) (10 18314.1736060128 1011.0818251137 0.0) (10 18282.2934594771
1007.1047158931 0.0) (10 18261.6911764706 1018.0995475113 0.0))
((0 . "LWPOLYLINE") (100 . "AcDbEntity") (8 . "PLANTS") (62 . 94) (370 . 13) (100 . "AcDbPolyline") (90 . 3) (70 . 0)
(43 . 0.0) (10 18280.5429864253 1048.2664027149) (10 18270.2871040724 1044.3404977376) (10 18261.6911764706
1018.0995475113))
((0 . "LWPOLYLINE") (100 . "AcDbEntity") (8 . "PLANTS") (62 . 94) (370 . 13) (100 . "AcDbPolyline") (90 . 2) (70 . 0)
(43 . 0.0) (10 18273.0033936652 3932.8804298643) (10 18265.4581447964 3940.4227375566))
((0 . "LWPOLYLINE") (100 . "AcDbEntity") (8 . "PLANTS") (62 . 94) (370 . 13) (100 . "AcDbPolyline") (90 . 2) (70 . 0)
(43 . 0.0) (10 18269.2307692308 3955.5048642534) (10 18265.4581447964 3940.4227375566))
((0 . "LWPOLYLINE") (100 . "AcDbEntity") (8 . "PLANTS") (62 . 94) (370 . 13) (100 . "AcDbPolyline") (90 . 2) (70 . 0)
(43 . 0.0) (10 18284.3156108597 3970.5882352941) (10 18280.5429864253 3963.0471719457))
((0 . "LWPOLYLINE") (100 . "AcDbEntity") (8 . "PLANTS") (62 . 94) (370 . 13) (100 . "AcDbPolyline") (90 . 2) (70 . 0)
(43 . 0.0) (10 18306.9400452489 3925.3393665158) (10 18284.3156108597 3921.5682126697))
((0 . "LWPOLYLINE") (100 . "AcDbEntity") (8 . "PLANTS") (62 . 94) (370 . 13) (100 . "AcDbPolyline") (90 . 2) (70 . 0)
(43 . 0.0) (10 18306.9400452489 1082.2030542986) (10 18288.0825791855 1089.7426470588))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18359.7285067874 1112.3670814479 0.0) (10 18356.2348612055 1170.6403508694 0.0) (10 18283.6373375105
1127.2647359874 0.0) (10 18288.0825791855 1089.7426470588 0.0))
((0 . "LWPOLYLINE") (100 . "AcDbEntity") (8 . "PLANTS") (62 . 94) (370 . 13) (100 . "AcDbPolyline") (90 . 3) (70 . 0)
(43 . 0.0) (10 18329.564479638 4004.5248868778) (10 18314.4796380091 4003.4682126697) (10 18295.6278280543
3989.4415158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18306.9400452489 3925.3393665158 0.0) (10 18323.2261891522 3906.8303314689 0.0) (10 18344.7475153502
3936.5142152021 0.0) (10 18363.5011312217 3921.5682126697 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18306.9400452488 3925.3393665158 0.0) (10 18301.3788580559 3971.85949477 0.0) (10 18375.7828302262
3978.4767440526 0.0) (10 18397.4377828054 3947.963800905 0.0))
((0 . "LWPOLYLINE") (100 . "AcDbEntity") (8 . "PLANTS") (62 . 94) (370 . 13) (100 . "AcDbPolyline") (90 . 3) (70 . 0)
(43 . 0.0) (10 18329.564479638 1029.4117647059) (10 18311.757918552 1052.036199095) (10 18306.9400452489
1082.2030542986))
((0 . "LWPOLYLINE") (100 . "AcDbEntity") (8 . "PLANTS") (62 . 94) (370 . 13) (100 . "AcDbPolyline") (90 . 2) (70 . 0)
(43 . 0.0) (10 18359.7285067873 1112.367081448) (10 18306.9400452489 1082.2030542986))
((0 . "LWPOLYLINE") (100 . "AcDbEntity") (8 . "PLANTS") (62 . 94) (370 . 13) (100 . "AcDbPolyline") (90 . 2) (70 . 0)
(43 . 0.0) (10 18314.4796380091 3849.925) (10 18314.4796380091 3880.0904977376))
((0 . "LWPOLYLINE") (100 . "AcDbEntity") (8 . "PLANTS") (62 . 94) (370 . 13) (100 . "AcDbPolyline") (90 . 2) (70 . 0)
(43 . 0.0) (10 18314.4796380091 3880.0904977376) (10 18355.9558823529 3883.8616515837))
((0 . "LWPOLYLINE") (100 . "AcDbEntity") (8 . "PLANTS") (62 . 94) (370 . 13) (100 . "AcDbPolyline") (90 . 2) (70 . 0)
(43 . 0.0) (10 18314.4796380091 3849.925) (10 18322.0192307692 3846.1538461538))
((0 . "LWPOLYLINE") (100 . "AcDbEntity") (8 . "PLANTS") (62 . 94) (370 . 13) (100 . "AcDbPolyline") (90 . 2) (70 . 0)
(43 . 0.0) (10 18318.2522624434 3834.8416289593) (10 18322.0192307692 3846.1538461538))
((0 . "LWPOLYLINE") (100 . "AcDbEntity") (8 . "PLANTS") (62 . 94) (370 . 13) (100 . "AcDbPolyline") (90 . 3) (70 . 0)
(43 . 0.0) (10 18322.0192307692 3846.1538461538) (10 18348.4093891403 3846.3019230769) (10 18355.9558823529 3849.925))
((0 . "LWPOLYLINE") (100 . "AcDbEntity") (8 . "PLANTS") (62 . 94) (370 . 13) (100 . "AcDbPolyline") (90 . 2) (70 . 0)
(43 . 0.0) (10 18329.564479638 1214.1770361991) (10 18346.9848022517 1234.786113001))
((0 . "LWPOLYLINE") (100 . "AcDbEntity") (8 . "PLANTS") (62 . 94) (370 . 13) (100 . "AcDbPolyline") (90 . 3) (70 . 0)
(43 . 0.0) (10 18352.0932240808 1238.6174293728) (10 18367.2680995475 1247.0580316742) (10 18420.0622171946
1251.8863122172))
((0 . "LWPOLYLINE") (100 . "AcDbEntity") (8 . "PLANTS") (62 . 94) (370 . 13) (100 . "AcDbPolyline") (90 . 3) (70 . 0)
(43 . 0.0) (10 18329.564479638 1029.4117647059) (10 18371.0407239819 1029.5664027149) (10 18386.1255656109
1036.9541855204))
((0 . "LWPOLYLINE") (100 . "AcDbEntity") (8 . "PLANTS") (62 . 94) (370 . 13) (100 . "AcDbPolyline") (90 . 2) (70 . 0)
(43 . 0.0) (10 18355.9558823529 3849.925) (10 18355.9558823529 3883.8616515837))
((0 . "LWPOLYLINE") (100 . "AcDbEntity") (8 . "PLANTS") (62 . 94) (370 . 13) (100 . "AcDbPolyline") (90 . 2) (70 . 0)
(43 . 0.0) (10 18363.5011312217 3887.631561086) (10 18355.9558823529 3883.8616515837))
((0 . "LWPOLYLINE") (100 . "AcDbEntity") (8 . "PLANTS") (62 . 94) (370 . 13) (100 . "AcDbPolyline") (90 . 2) (70 . 0)
(43 . 0.0) (10 18386.1255656109 3849.925) (10 18355.9558823529 3849.925))
((0 . "LWPOLYLINE") (100 . "AcDbEntity") (8 . "PLANTS") (62 . 94) (370 . 13) (100 . "AcDbPolyline") (90 . 2) (70 . 0)
(43 . 0.0) (10 18389.8925339367 1112.367081448) (10 18359.7285067873 1112.367081448))
((0 . "LWPOLYLINE") (100 . "AcDbEntity") (8 . "PLANTS") (62 . 94) (370 . 13) (100 . "AcDbPolyline") (90 . 3) (70 . 0)
(43 . 0.0) (10 18363.5011312217 3921.5682126697) (10 18359.7354072398 3910.2559954751) (10 18363.5011312217
3887.631561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18363.5011312217 3921.5682126697 0.0) (10 18376.7579749263 3919.800606138 0.0) (10 18401.8880740346
3929.9330011392 0.0) (10 18397.4377828054 3947.963800905 0.0))
((0 . "LWPOLYLINE") (100 . "AcDbEntity") (8 . "PLANTS") (62 . 94) (370 . 13) (100 . "AcDbPolyline") (90 . 2) (70 . 0)
(43 . 0.0) (10 18374.8133484163 3887.631561086) (10 18363.5011312217 3887.631561086))
((0 . "LWPOLYLINE") (100 . "AcDbEntity") (8 . "PLANTS") (62 . 94) (370 . 13) (100 . "AcDbPolyline") (90 . 2) (70 . 0)
(43 . 0.0) (10 18363.5011312217 1157.6159502262) (10 18363.5011312217 1168.9281674208))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18427.6018099548 1161.3885746606 0.0) (10 18403.1212280315 1156.2137116933 0.0) (10 18388.5374886633
1191.1639872358 0.0) (10 18363.5011312217 1168.9281674208 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18427.6018099548 1161.3885746606 0.0) (10 18437.5691735718 1196.640110383 0.0) (10 18398.3719483096
1212.3092901597 0.0) (10 18371.0407239819 1214.1770361991 0.0))
((0 . "LWPOLYLINE") (100 . "AcDbEntity") (8 . "PLANTS") (62 . 94) (370 . 13) (100 . "AcDbPolyline") (90 . 3) (70 . 0)
(43 . 0.0) (10 18374.8133484163 3887.631561086) (10 18385.067760181 3872.5494343891) (10 18386.1255656109 3849.925))
((0 . "LWPOLYLINE") (100 . "AcDbEntity") (8 . "PLANTS") (62 . 94) (370 . 13) (100 . "AcDbPolyline") (90 . 2) (70 . 0)
(43 . 0.0) (10 18386.1255656109 3902.7149321267) (10 18374.8133484163 3887.631561086))
((0 . "LWPOLYLINE") (100 . "AcDbEntity") (8 . "PLANTS") (62 . 94) (370 . 13) (100 . "AcDbPolyline") (90 . 3) (70 . 0)
(43 . 0.0) (10 18438.9140271493 3857.4660633484) (10 18420.0622171946 3850.0728506787) (10 18386.1255656109 3849.925))
((0 . "LWPOLYLINE") (100 . "AcDbEntity") (8 . "PLANTS") (62 . 94) (370 . 13) (100 . "AcDbPolyline") (90 . 2) (70 . 0)
(43 . 0.0) (10 18386.1255656109 1134.9915158371) (10 18389.8925339367 1119.9095022624))
((0 . "LWPOLYLINE") (100 . "AcDbEntity") (8 . "PLANTS") (62 . 94) (370 . 13) (100 . "AcDbPolyline") (90 . 3) (70 . 0)
(43 . 0.0) (10 18431.3744343891 1029.4117647059) (10 18397.4377828054 1029.5664027149) (10 18386.1255656109
1036.9541855204))
((0 . "LWPOLYLINE") (100 . "AcDbEntity") (8 . "PLANTS") (62 . 94) (370 . 13) (100 . "AcDbPolyline") (90 . 3) (70 . 0)
(43 . 0.0) (10 18386.1255656109 1036.9541855204) (10 18393.5174208145 1063.3484162896) (10 18393.665158371
1085.9728506787))
((0 . "LWPOLYLINE") (100 . "AcDbEntity") (8 . "PLANTS") (62 . 94) (370 . 13) (100 . "AcDbPolyline") (90 . 3) (70 . 0)
(43 . 0.0) (10 18427.6018099548 1108.5972850679) (10 18416.2895927602 1114.9410633484) (10 18389.8925339367
1119.9095022624))
((0 . "LWPOLYLINE") (100 . "AcDbEntity") (8 . "PLANTS") (62 . 94) (370 . 13) (100 . "AcDbPolyline") (90 . 2) (70 . 0)
(43 . 0.0) (10 18389.8925339367 1112.367081448) (10 18389.8925339367 1119.9095022624))
((0 . "LWPOLYLINE") (100 . "AcDbEntity") (8 . "PLANTS") (62 . 94) (370 . 13) (100 . "AcDbPolyline") (90 . 2) (70 . 0)
(43 . 0.0) (10 18389.8925339367 1112.367081448) (10 18393.665158371 1085.9728506787))
((0 . "LWPOLYLINE") (100 . "AcDbEntity") (8 . "PLANTS") (62 . 94) (370 . 13) (100 . "AcDbPolyline") (90 . 3) (70 . 0)
(43 . 0.0) (10 18423.8291855204 1093.5152714932) (10 18408.75 1093.3599547511) (10 18393.665158371 1085.9728506787))
((0 . "LWPOLYLINE") (100 . "AcDbEntity") (8 . "PLANTS") (62 . 94) (370 . 13) (100 . "AcDbPolyline") (90 . 3) (70 . 0)
(43 . 0.0) (10 18442.6866515837 3955.5048642534) (10 18416.2895927602 3948.1118778281) (10 18397.4377828054
3947.963800905))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.3164986946)
(40 . 0.563877757) (40 . 0.8210808032) (40 . 1) (40 . 1) (40 . 1) (40 . 1) (10 18416.2895927602 4061.0859728507 0.0) (10
18413.4378886416 4062.8504807817 0.0) (10 18347.3949354053 4067.9482495676 0.0) (10 18356.5909067254 4013.3429114246
0.0) (10 18405.479817943 4008.1058535005 0.0) (10 18399.1850327943 3969.2708171369 0.0) (10 18427.6018099547
3993.2126696832 0.0))
((0 . "LWPOLYLINE") (100 . "AcDbEntity") (8 . "PLANTS") (62 . 94) (370 . 13) (100 . "AcDbPolyline") (90 . 3) (70 . 0)
(43 . 0.0) (10 18423.8291855204 1093.5152714932) (10 18430.3235294118 1089.5893665158) (10 18446.4536199095
1063.3484162896))
((0 . "LWPOLYLINE") (100 . "AcDbEntity") (8 . "PLANTS") (62 . 94) (370 . 13) (100 . "AcDbPolyline") (90 . 2) (70 . 0)
(43 . 0.0) (10 18423.8291855204 1093.5152714932) (10 18427.6018099548 1108.5972850679))
((0 . "LWPOLYLINE") (100 . "AcDbEntity") (8 . "PLANTS") (62 . 94) (370 . 13) (100 . "AcDbPolyline") (90 . 3) (70 . 0)
(43 . 0.0) (10 18453.9988687783 4057.3148190045) (10 18442.6866515837 4049.9349547511) (10 18427.6018099548
4057.3148190045))
((0 . "LWPOLYLINE") (100 . "AcDbEntity") (8 . "PLANTS") (62 . 94) (370 . 13) (100 . "AcDbPolyline") (90 . 3) (70 . 0)
(43 . 0.0) (10 18427.6018099548 3993.2126696833) (10 18432.5702488688 3974.3656108597) (10 18442.6866515837
3966.817081448))
((0 . "LWPOLYLINE") (100 . "AcDbEntity") (8 . "PLANTS") (62 . 94) (370 . 13) (100 . "AcDbPolyline") (90 . 2) (70 . 0)
(43 . 0.0) (10 18427.6018099548 3993.2126696833) (10 18431.3744343891 4023.3781674208))
((0 . "LWPOLYLINE") (100 . "AcDbEntity") (8 . "PLANTS") (62 . 94) (370 . 13) (100 . "AcDbPolyline") (90 . 3) (70 . 0)
(43 . 0.0) (10 18427.6018099548 1161.3885746606) (10 18428.8059954751 1153.8399321267) (10 18438.9140271493
1142.5339366516))
((0 . "LWPOLYLINE") (100 . "AcDbEntity") (8 . "PLANTS") (62 . 94) (370 . 13) (100 . "AcDbPolyline") (90 . 2) (70 . 0)
(43 . 0.0) (10 18427.6018099548 1108.5972850679) (10 18438.9140271493 1112.367081448))
((0 . "LWPOLYLINE") (100 . "AcDbEntity") (8 . "PLANTS") (62 . 94) (370 . 13) (100 . "AcDbPolyline") (90 . 2) (70 . 0)
(43 . 0.0) (10 18674.446625672 3367.2700226244) (10 18684.0101809955 3367.2700226244))
((0 . "LWPOLYLINE") (100 . "AcDbEntity") (8 . "PLANTS") (62 . 94) (370 . 13) (100 . "AcDbPolyline") (90 . 2) (70 . 0)
(43 . 0.0) (10 18431.3744343891 1029.4117647059) (10 18446.4536199095 1014.3297511312))
((0 . "LWPOLYLINE") (100 . "AcDbEntity") (8 . "PLANTS") (62 . 94) (370 . 13) (100 . "AcDbPolyline") (90 . 3) (70 . 0)
(43 . 0.0) (10 18431.3744343891 1029.4117647059) (10 18441.4880090498 1044.4937782805) (10 18446.4536199095
1063.3484162896))
((0 . "LWPOLYLINE") (100 . "AcDbEntity") (8 . "PLANTS") (62 . 94) (370 . 13) (100 . "AcDbPolyline") (90 . 3) (70 . 0)
(43 . 0.0) (10 18438.9140271493 3883.8616515837) (10 18476.6233031674 3883.7132352941) (10 18495.4751131222
3876.3193438914))
((0 . "LWPOLYLINE") (100 . "AcDbEntity") (8 . "PLANTS") (62 . 94) (370 . 13) (100 . "AcDbPolyline") (90 . 2) (70 . 0)
(43 . 0.0) (10 18438.9140271493 3883.8616515837) (10 18438.9140271493 3857.4660633484))
((0 . "LWPOLYLINE") (100 . "AcDbEntity") (8 . "PLANTS") (62 . 94) (370 . 13) (100 . "AcDbPolyline") (90 . 2) (70 . 0)
(43 . 0.0) (10 18446.4536199095 3944.1926470588) (10 18438.9140271493 3883.8616515837))
((0 . "LWPOLYLINE") (100 . "AcDbEntity") (8 . "PLANTS") (62 . 94) (370 . 13) (100 . "AcDbPolyline") (90 . 3) (70 . 0)
(43 . 0.0) (10 18491.7024886878 3853.6949095023) (10 18457.7658371041 3850.0728506787) (10 18438.9140271493
3857.4660633484))
((0 . "LWPOLYLINE") (100 . "AcDbEntity") (8 . "PLANTS") (62 . 94) (370 . 13) (100 . "AcDbPolyline") (90 . 2) (70 . 0)
(43 . 0.0) (10 18438.9140271493 1142.5339366516) (10 18438.9140271493 1112.367081448))
((0 . "LWPOLYLINE") (100 . "AcDbEntity") (8 . "PLANTS") (62 . 94) (370 . 13) (100 . "AcDbPolyline") (90 . 3) (70 . 0)
(43 . 0.0) (10 18465.3110859729 1153.8461538462) (10 18461.3851809955 1147.5023755656) (10 18438.9140271493
1142.5339366516))
((0 . "LWPOLYLINE") (100 . "AcDbEntity") (8 . "PLANTS") (62 . 94) (370 . 13) (100 . "AcDbPolyline") (90 . 3) (70 . 0)
(43 . 0.0) (10 18514.3269230769 1108.5972850679) (10 18446.4619909502 1108.7450226244) (10 18438.9140271493
1112.367081448))
((0 . "LWPOLYLINE") (100 . "AcDbEntity") (8 . "PLANTS") (62 . 94) (370 . 13) (100 . "AcDbPolyline") (90 . 2) (70 . 0)
(43 . 0.0) (10 18442.6866515837 3955.5048642534) (10 18442.6866515837 3966.817081448))
((0 . "LWPOLYLINE") (100 . "AcDbEntity") (8 . "PLANTS") (62 . 94) (370 . 13) (100 . "AcDbPolyline") (90 . 2) (70 . 0)
(43 . 0.0) (10 18480.3902714932 4000.7537330317) (10 18442.6866515837 3966.817081448))
((0 . "LWPOLYLINE") (100 . "AcDbEntity") (8 . "PLANTS") (62 . 94) (370 . 13) (100 . "AcDbPolyline") (90 . 2) (70 . 0)
(43 . 0.0) (10 18446.4536199095 3944.1926470588) (10 18442.6866515837 3955.5048642534))
((0 . "LWPOLYLINE") (100 . "AcDbEntity") (8 . "PLANTS") (62 . 94) (370 . 13) (100 . "AcDbPolyline") (90 . 2) (70 . 0)
(43 . 0.0) (10 18442.6866515837 987.9326923077) (10 18446.4536199095 1014.3297511312))
((0 . "LWPOLYLINE") (100 . "AcDbEntity") (8 . "PLANTS") (62 . 94) (370 . 13) (100 . "AcDbPolyline") (90 . 3) (70 . 0)
(43 . 0.0) (10 18446.4536199095 3944.1926470588) (10 18469.0780542986 3936.7996606335) (10 18495.4751131222
3936.6515837104))
((0 . "LWPOLYLINE") (100 . "AcDbEntity") (8 . "PLANTS") (62 . 94) (370 . 13) (100 . "AcDbPolyline") (90 . 2) (70 . 0)
(43 . 0.0) (10 18446.4536199095 1063.3484162896) (10 18472.850678733 1063.3484162896))
((0 . "LWPOLYLINE") (100 . "AcDbEntity") (8 . "PLANTS") (62 . 94) (370 . 13) (100 . "AcDbPolyline") (90 . 3) (70 . 0)
(43 . 0.0) (10 18548.2635746606 1025.6419683258) (10 18521.8721719457 1010.7055429864) (10 18446.4536199095
1014.3297511312))
((0 . "LWPOLYLINE") (100 . "AcDbEntity") (8 . "PLANTS") (62 . 94) (370 . 13) (100 . "AcDbPolyline") (90 . 3) (70 . 0)
(43 . 0.0) (10 18465.3110859729 1180.2403846154) (10 18455.1946832579 1187.7897058824) (10 18450.2262443439
1202.8648190045))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18480.3902714932 4000.7537330317 0.0) (10 18479.2597293074 4021.2410717866 0.0) (10 18473.8650687733
4047.9525120063 0.0) (10 18453.9988687783 4057.3148190045 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18453.9988687783 4057.3148190045 0.0) (10 18483.3903102188 4084.1551666544 0.0) (10 18441.1208202419
4113.9437760604 0.0) (10 18450.2448820061 4140.2854714594 0.0))
((0 . "LWPOLYLINE") (100 . "AcDbEntity") (8 . "PLANTS") (62 . 94) (370 . 13) (100 . "AcDbPolyline") (90 . 3) (70 . 0)
(43 . 0.0) (10 18472.8227090804 4157.218841765) (10 18506.7873303167 4141.3281674208) (10 18529.4117647059
4136.5003393665))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18533.1843891403 1263.1985294118 0.0) (10 18494.9654070365 1264.8464433245 0.0) (10 18494.6913680525
1307.5379132404 0.0) (10 18471.6452851777 1328.2814751955 0.0))
((0 . "LWPOLYLINE") (100 . "AcDbEntity") (8 . "PLANTS") (62 . 94) (370 . 13) (100 . "AcDbPolyline") (90 . 3) (70 . 0)
(43 . 0.0) (10 18448.8124706994 1311.1568643367) (10 18465.1618778281 1266.9683257919) (10 18461.5384615385
1230.517760181))
((0 . "LWPOLYLINE") (100 . "AcDbEntity") (8 . "PLANTS") (62 . 94) (370 . 13) (100 . "AcDbPolyline") (90 . 3) (70 . 0)
(43 . 0.0) (10 18491.7024886878 3853.6949095023) (10 18479.1944570136 3815.9883484163) (10 18465.3110859729
3800.9049773756))
((0 . "LWPOLYLINE") (100 . "AcDbEntity") (8 . "PLANTS") (62 . 94) (370 . 13) (100 . "AcDbPolyline") (90 . 2) (70 . 0)
(43 . 0.0) (10 18465.3110859729 1180.2403846154) (10 18465.3110859729 1153.8461538462))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6031301508) (40
. 1) (40 . 1) (40 . 1) (40 . 1) (10 18465.3110859728 1180.2403846154 0.0) (10 18484.5693191588 1224.4675859054 0.0) (10
18528.6148499696 1175.482069985 0.0) (10 18481.8555653436 1149.364824468 0.0) (10 18465.3110859728 1153.8461538462 0.0))
((0 . "LWPOLYLINE") (100 . "AcDbEntity") (8 . "PLANTS") (62 . 94) (370 . 13) (100 . "AcDbPolyline") (90 . 2) (70 . 0)
(43 . 0.0) (10 18480.3902714932 4000.7537330317) (10 18510.5599547511 3989.4415158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18487.935520362 4076.1693438914 0.0) (10 18508.4554367885 4053.9782914924 0.0) (10 18523.3798284387
4017.9523724794 0.0) (10 18510.5599547511 3989.4415158371 0.0))
((0 . "LWPOLYLINE") (100 . "AcDbEntity") (8 . "PLANTS") (62 . 94) (370 . 13) (100 . "AcDbPolyline") (90 . 2) (70 . 0)
(43 . 0.0) (10 18491.7024886878 3853.6949095023) (10 18499.2477375566 3857.4660633484))
((0 . "LWPOLYLINE") (100 . "AcDbEntity") (8 . "PLANTS") (62 . 94) (370 . 13) (100 . "AcDbPolyline") (90 . 2) (70 . 0)
(43 . 0.0) (10 18495.4751131222 3876.3193438914) (10 18495.4751131222 3936.6515837104))
((0 . "LWPOLYLINE") (100 . "AcDbEntity") (8 . "PLANTS") (62 . 94) (370 . 13) (100 . "AcDbPolyline") (90 . 2) (70 . 0)
(43 . 0.0) (10 18518.0995475113 3940.4227375566) (10 18495.4751131222 3936.6515837104))
((0 . "LWPOLYLINE") (100 . "AcDbEntity") (8 . "PLANTS") (62 . 94) (370 . 13) (100 . "AcDbPolyline") (90 . 2) (70 . 0)
(43 . 0.0) (10 18499.2477375566 3868.778280543) (10 18495.4751131222 3876.3193438914))
((0 . "LWPOLYLINE") (100 . "AcDbEntity") (8 . "PLANTS") (62 . 94) (370 . 13) (100 . "AcDbPolyline") (90 . 2) (70 . 0)
(43 . 0.0) (10 18499.2477375566 3857.4660633484) (10 18499.2477375566 3868.778280543))
((0 . "LWPOLYLINE") (100 . "AcDbEntity") (8 . "PLANTS") (62 . 94) (370 . 13) (100 . "AcDbPolyline") (90 . 2) (70 . 0)
(43 . 0.0) (10 18544.4966063348 3910.2559954751) (10 18499.2477375566 3868.778280543))
((0 . "LWPOLYLINE") (100 . "AcDbEntity") (8 . "PLANTS") (62 . 94) (370 . 13) (100 . "AcDbPolyline") (90 . 3) (70 . 0)
(43 . 0.0) (10 18499.2477375566 3857.4660633484) (10 18567.121040724 3846.3084841629) (10 18589.7454751131
3861.2372171946))
((0 . "LWPOLYLINE") (100 . "AcDbEntity") (8 . "PLANTS") (62 . 94) (370 . 13) (100 . "AcDbPolyline") (90 . 2) (70 . 0)
(43 . 0.0) (10 18499.2477375566 1048.2664027149) (10 18499.2477375566 1036.9541855204))
((0 . "LWPOLYLINE") (100 . "AcDbEntity") (8 . "PLANTS") (62 . 94) (370 . 13) (100 . "AcDbPolyline") (90 . 2) (70 . 0)
(43 . 0.0) (10 18499.2477375566 935.1442307692) (10 18499.2477375566 969.0808823529))
((0 . "LWPOLYLINE") (100 . "AcDbEntity") (8 . "PLANTS") (62 . 94) (370 . 13) (100 . "AcDbPolyline") (90 . 2) (70 . 0)
(43 . 0.0) (10 18499.2477375566 935.1442307692) (10 18529.4117647059 935.1442307692))
((0 . "LWPOLYLINE") (100 . "AcDbEntity") (8 . "PLANTS") (62 . 94) (370 . 13) (100 . "AcDbPolyline") (90 . 3) (70 . 0)
(43 . 0.0) (10 18510.5599547511 3989.4415158371) (10 18515.5200226244 3974.5133484163) (10 18521.8721719457
3970.5882352941))
((0 . "LWPOLYLINE") (100 . "AcDbEntity") (8 . "PLANTS") (62 . 94) (370 . 13) (100 . "AcDbPolyline") (90 . 3) (70 . 0)
(43 . 0.0) (10 18514.3269230769 1108.5972850679) (10 18523.0748868778 1082.2030542986) (10 18536.9513574661
1067.1182126697))
((0 . "LWPOLYLINE") (100 . "AcDbEntity") (8 . "PLANTS") (62 . 94) (370 . 13) (100 . "AcDbPolyline") (90 . 3) (70 . 0)
(43 . 0.0) (10 18533.1843891403 1127.4519230769) (10 18522.0254524887 1123.5260180995) (10 18514.3269230769
1108.5972850679))
((0 . "LWPOLYLINE") (100 . "AcDbEntity") (8 . "PLANTS") (62 . 94) (370 . 13) (100 . "AcDbPolyline") (90 . 2) (70 . 0)
(43 . 0.0) (10 18529.4117647059 3940.4227375566) (10 18518.0995475113 3940.4227375566))
((0 . "LWPOLYLINE") (100 . "AcDbEntity") (8 . "PLANTS") (62 . 94) (370 . 13) (100 . "AcDbPolyline") (90 . 2) (70 . 0)
(43 . 0.0) (10 18518.0995475113 3940.4227375566) (10 18521.8721719457 3970.5882352941))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3937717617)
(40 . 0.8921100703) (40 . 1) (40 . 1) (40 . 1) (40 . 1) (10 18521.8721719457 3970.5882352941 0.0) (10 18549.6162504982
3981.1463712603 0.0) (10 18544.4589482825 4039.6303034197 0.0) (10 18524.5306118235 4091.6582397644 0.0) (10
18534.3014577599 4131.0318524729 0.0) (10 18529.411764706 4136.5003393665 0.0))
((0 . "LWPOLYLINE") (100 . "AcDbEntity") (8 . "PLANTS") (62 . 94) (370 . 13) (100 . "AcDbPolyline") (90 . 2) (70 . 0)
(43 . 0.0) (10 18533.3010593864 4148.2028067397) (10 18529.4117647059 4136.5003393665))
((0 . "LWPOLYLINE") (100 . "AcDbEntity") (8 . "PLANTS") (62 . 94) (370 . 13) (100 . "AcDbPolyline") (90 . 2) (70 . 0)
(43 . 0.0) (10 18529.4117647059 3940.4227375566) (10 18544.4966063348 3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18529.4117647059 3940.4227375566 0.0) (10 18569.9813514203 3932.1631395139 0.0) (10 18563.8202987968
3977.2019999559 0.0) (10 18589.7454751131 3985.6716063348 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18604.8246606335 935.1442307692 0.0) (10 18579.2671582477 964.3330454435 0.0) (10 18553.2861894851
918.4736946297 0.0) (10 18529.4117647059 935.1442307692 0.0))
((0 . "LWPOLYLINE") (100 . "AcDbEntity") (8 . "PLANTS") (62 . 94) (370 . 13) (100 . "AcDbPolyline") (90 . 2) (70 . 0)
(43 . 0.0) (10 18533.1843891403 976.6204751131) (10 18529.4117647059 935.1442307692))
((0 . "LWPOLYLINE") (100 . "AcDbEntity") (8 . "PLANTS") (62 . 94) (370 . 13) (100 . "AcDbPolyline") (90 . 3) (70 . 0)
(43 . 0.0) (10 18533.1843891403 1263.1985294118) (10 18533.3376696833 1229.2618778281) (10 18540.7239819005
1217.9496606335))
((0 . "LWPOLYLINE") (100 . "AcDbEntity") (8 . "PLANTS") (62 . 94) (370 . 13) (100 . "AcDbPolyline") (90 . 2) (70 . 0)
(43 . 0.0) (10 18533.1843891403 1263.1985294118) (10 18548.2635746606 1266.9683257919))
((0 . "LWPOLYLINE") (100 . "AcDbEntity") (8 . "PLANTS") (62 . 94) (370 . 13) (100 . "AcDbPolyline") (90 . 2) (70 . 0)
(43 . 0.0) (10 18533.1843891403 1127.4519230769) (10 18570.8880090498 1127.4519230769))
((0 . "LWPOLYLINE") (100 . "AcDbEntity") (8 . "PLANTS") (62 . 94) (370 . 13) (100 . "AcDbPolyline") (90 . 3) (70 . 0)
(43 . 0.0) (10 18533.1843891403 1127.4519230769) (10 18533.3307692308 1172.7007918552) (10 18540.7239819005
1217.9496606335))
((0 . "LWPOLYLINE") (100 . "AcDbEntity") (8 . "PLANTS") (62 . 94) (370 . 13) (100 . "AcDbPolyline") (90 . 3) (70 . 0)
(43 . 0.0) (10 18574.6606334842 1055.8059954751) (10 18559.5757918552 1065.9148190045) (10 18536.9513574661
1067.1182126697))
((0 . "LWPOLYLINE") (100 . "AcDbEntity") (8 . "PLANTS") (62 . 94) (370 . 13) (100 . "AcDbPolyline") (90 . 3) (70 . 0)
(43 . 0.0) (10 18536.9513574661 1067.1182126697) (10 18537.1074660633 1044.4937782805) (10 18548.2635746606
1025.6419683258))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18589.7435520362 4091.2514705882 0.0) (10 18565.1173591704 4080.2131903495 0.0) (10 18538.2661172512
4109.2125469367 0.0) (10 18552.4413135832 4135.0438819794 0.0))
((0 . "LWPOLYLINE") (100 . "AcDbEntity") (8 . "PLANTS") (62 . 94) (370 . 13) (100 . "AcDbPolyline") (90 . 2) (70 . 0)
(43 . 0.0) (10 18548.2635746606 1217.9496606335) (10 18540.7239819005 1217.9496606335))
((0 . "LWPOLYLINE") (100 . "AcDbEntity") (8 . "PLANTS") (62 . 94) (370 . 13) (100 . "AcDbPolyline") (90 . 2) (70 . 0)
(43 . 0.0) (10 18593.5124434389 3898.9437782805) (10 18544.4966063348 3910.2559954751))
((0 . "LWPOLYLINE") (100 . "AcDbEntity") (8 . "PLANTS") (62 . 94) (370 . 13) (100 . "AcDbPolyline") (90 . 3) (70 . 0)
(43 . 0.0) (10 18578.4332579186 1210.407239819) (10 18555.8128959276 1210.5618778281) (10 18548.2635746606
1217.9496606335))
((0 . "LWPOLYLINE") (100 . "AcDbEntity") (8 . "PLANTS") (62 . 94) (370 . 13) (100 . "AcDbPolyline") (90 . 2) (70 . 0)
(43 . 0.0) (10 18555.8069004525 1236.8014705882) (10 18548.2635746606 1217.9496606335))
((0 . "LWPOLYLINE") (100 . "AcDbEntity") (8 . "PLANTS") (62 . 94) (370 . 13) (100 . "AcDbPolyline") (90 . 2) (70 . 0)
(43 . 0.0) (10 18570.8880090498 1029.4117647059) (10 18548.2635746606 1025.6419683258))
((0 . "LWPOLYLINE") (100 . "AcDbEntity") (8 . "PLANTS") (62 . 94) (370 . 13) (100 . "AcDbPolyline") (90 . 2) (70 . 0)
(43 . 0.0) (10 18634.9943438914 3623.6806561086) (10 18631.6905785059 3622.0951101099))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18570.8880090498 1029.4117647059 0.0) (10 18587.017229637 1021.0515837511 0.0) (10 18577.9157098583
990.6409023314 0.0) (10 18567.121040724 980.3930995475 0.0))
((0 . "LWPOLYLINE") (100 . "AcDbEntity") (8 . "PLANTS") (62 . 94) (370 . 13) (100 . "AcDbPolyline") (90 . 2) (70 . 0)
(43 . 0.0) (10 18570.8880090498 1127.4519230769) (10 18574.6606334842 1119.9095022624))
((0 . "LWPOLYLINE") (100 . "AcDbEntity") (8 . "PLANTS") (62 . 94) (370 . 13) (100 . "AcDbPolyline") (90 . 3) (70 . 0)
(43 . 0.0) (10 18578.4332579186 1210.407239819) (10 18581.0044117647 1180.2403846154) (10 18570.8880090498
1127.4519230769))
((0 . "LWPOLYLINE") (100 . "AcDbEntity") (8 . "PLANTS") (62 . 94) (370 . 13) (100 . "AcDbPolyline") (90 . 2) (70 . 0)
(43 . 0.0) (10 18570.8880090498 1029.4117647059) (10 18578.4332579186 1048.2664027149))
((0 . "LWPOLYLINE") (100 . "AcDbEntity") (8 . "PLANTS") (62 . 94) (370 . 13) (100 . "AcDbPolyline") (90 . 2) (70 . 0)
(43 . 0.0) (10 18597.2850678733 1119.9095022624) (10 18574.6606334842 1119.9095022624))
((0 . "LWPOLYLINE") (100 . "AcDbEntity") (8 . "PLANTS") (62 . 94) (370 . 13) (100 . "AcDbPolyline") (90 . 2) (70 . 0)
(43 . 0.0) (10 18574.6606334842 1055.8059954751) (10 18574.6606334842 1119.9095022624))
((0 . "LWPOLYLINE") (100 . "AcDbEntity") (8 . "PLANTS") (62 . 94) (370 . 13) (100 . "AcDbPolyline") (90 . 2) (70 . 0)
(43 . 0.0) (10 18574.6606334842 1055.8059954751) (10 18578.4332579186 1048.2664027149))
((0 . "LWPOLYLINE") (100 . "AcDbEntity") (8 . "PLANTS") (62 . 94) (370 . 13) (100 . "AcDbPolyline") (90 . 2) (70 . 0)
(43 . 0.0) (10 18638.7613122172 3665.1583710407) (10 18628.0163118817 3663.143557552))
((0 . "LWPOLYLINE") (100 . "AcDbEntity") (8 . "PLANTS") (62 . 94) (370 . 13) (100 . "AcDbPolyline") (90 . 2) (70 . 0)
(43 . 0.0) (10 18585.9728506787 1048.2664027149) (10 18578.4332579186 1048.2664027149))
((0 . "LWPOLYLINE") (100 . "AcDbEntity") (8 . "PLANTS") (62 . 94) (370 . 13) (100 . "AcDbPolyline") (90 . 2) (70 . 0)
(43 . 0.0) (10 18589.7435520362 4091.2514705882) (10 18589.7435520362 4109.398593043))
((0 . "LWPOLYLINE") (100 . "AcDbEntity") (8 . "PLANTS") (62 . 94) (370 . 13) (100 . "AcDbPolyline") (90 . 3) (70 . 0)
(43 . 0.0) (10 18585.9728506787 1048.2664027149) (10 18601.0576923077 1030.6097285068) (10 18623.6821266968
1021.8693438914))
((0 . "LWPOLYLINE") (100 . "AcDbEntity") (8 . "PLANTS") (62 . 94) (370 . 13) (100 . "AcDbPolyline") (90 . 2) (70 . 0)
(43 . 0.0) (10 18585.9728506787 1048.2664027149) (10 18612.3699095023 1074.6606334842))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18589.7435520362 4091.2514705882 0.0) (10 18596.2874722073 4055.4283987581 0.0) (10 18579.0613881094
4021.1489680306 0.0) (10 18589.7454751131 3985.6716063348 0.0))
((0 . "LWPOLYLINE") (100 . "AcDbEntity") (8 . "PLANTS") (62 . 94) (370 . 13) (100 . "AcDbPolyline") (90 . 2) (70 . 0)
(43 . 0.0) (10 18642.5339366516 4004.5248868778) (10 18589.7454751131 3985.6716063348))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4290499203) (40
. 1) (40 . 1) (40 . 1) (40 . 1) (10 18638.7613122172 3763.1976244344 0.0) (10 18645.6182593359 3781.9617809739 0.0) (10
18617.093939678 3811.0891683109 0.0) (10 18620.5070009817 3852.83922412 0.0) (10 18589.7454751131 3861.2372171946 0.0))
((0 . "LWPOLYLINE") (100 . "AcDbEntity") (8 . "PLANTS") (62 . 94) (370 . 13) (100 . "AcDbPolyline") (90 . 3) (70 . 0)
(43 . 0.0) (10 18593.5124434389 3898.9437782805) (10 18589.8918552036 3891.3964932127) (10 18589.7454751131
3861.2372171946))
((0 . "LWPOLYLINE") (100 . "AcDbEntity") (8 . "PLANTS") (62 . 94) (370 . 13) (100 . "AcDbPolyline") (90 . 2) (70 . 0)
(43 . 0.0) (10 18593.5124434389 3793.3639140271) (10 18589.7454751131 3815.9883484163))
((0 . "LWPOLYLINE") (100 . "AcDbEntity") (8 . "PLANTS") (62 . 94) (370 . 13) (100 . "AcDbPolyline") (90 . 2) (70 . 0)
(43 . 0.0) (10 18593.5124434389 3898.9437782805) (10 18631.221719457 3910.2559954751))
((0 . "LWPOLYLINE") (100 . "AcDbEntity") (8 . "PLANTS") (62 . 94) (370 . 13) (100 . "AcDbPolyline") (90 . 3) (70 . 0)
(43 . 0.0) (10 18597.2850678733 1119.9095022624) (10 18603.6288461538 1112.3622171946) (10 18612.3699095023
1074.6606334842))
((0 . "LWPOLYLINE") (100 . "AcDbEntity") (8 . "PLANTS") (62 . 94) (370 . 13) (100 . "AcDbPolyline") (90 . 2) (70 . 0)
(43 . 0.0) (10 18597.2850678733 1119.9095022624) (10 18616.1368778281 1127.4519230769))
((0 . "LWPOLYLINE") (100 . "AcDbEntity") (8 . "PLANTS") (62 . 94) (370 . 13) (100 . "AcDbPolyline") (90 . 2) (70 . 0)
(43 . 0.0) (10 18606.239393028 3744.3438914027) (10 18608.5972850679 3763.1976244344))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18604.8246606335 935.1442307692 0.0) (10 18639.8025077554 926.0503157992 0.0) (10 18679.5358186297
949.0252513673 0.0) (10 18714.1798642534 931.3716063348 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.6013184721)
(40 . 0.8386754414) (40 . 1) (40 . 1) (40 . 1) (40 . 1) (10 18604.8246606335 935.1442307692 0.0) (10 18604.2912605443
970.1442706279 0.0) (10 18634.2662360761 1013.1473420891 0.0) (10 18692.9509520081 1013.9214458959 0.0) (10
18712.0299028526 1021.2974336949 0.0) (10 18721.7194570136 1018.0995475113 0.0))
((0 . "LWPOLYLINE") (100 . "AcDbEntity") (8 . "PLANTS") (62 . 94) (370 . 13) (100 . "AcDbPolyline") (90 . 3) (70 . 0)
(43 . 0.0) (10 18638.7613122172 3763.1976244344) (10 18631.2148190045 3763.1976244344) (10 18608.5972850679
3763.1976244344))
((0 . "LWPOLYLINE") (100 . "AcDbEntity") (8 . "PLANTS") (62 . 94) (370 . 13) (100 . "AcDbPolyline") (90 . 3) (70 . 0)
(43 . 0.0) (10 18668.9309954751 3699.0950226244) (10 18646.306561086 3692.7512443439) (10 18625.4254573354
3692.0882606868))
((0 . "LWPOLYLINE") (100 . "AcDbEntity") (8 . "PLANTS") (62 . 94) (370 . 13) (100 . "AcDbPolyline") (90 . 3) (70 . 0)
(43 . 0.0) (10 18631.221719457 1214.1770361991) (10 18616.2929864253 1209.3509049774) (10 18612.3699095023
1199.0950226244))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18612.3699095023 1074.6606334842 0.0) (10 18637.941511063 1067.6438503092 0.0) (10 18664.8385459858
1082.2625509599 0.0) (10 18676.4705882353 1104.8274886878 0.0))
((0 . "LWPOLYLINE") (100 . "AcDbEntity") (8 . "PLANTS") (62 . 94) (370 . 13) (100 . "AcDbPolyline") (90 . 2) (70 . 0)
(43 . 0.0) (10 18616.1368778281 1127.4519230769) (10 18623.6821266968 1127.4519230769))
((0 . "LWPOLYLINE") (100 . "AcDbEntity") (8 . "PLANTS") (62 . 94) (370 . 13) (100 . "AcDbPolyline") (90 . 3) (70 . 0)
(43 . 0.0) (10 18638.7613122172 1157.6159502262) (10 18624.7371040724 1149.921040724) (10 18616.1368778281
1127.4519230769))
((0 . "LWPOLYLINE") (100 . "AcDbEntity") (8 . "PLANTS") (62 . 94) (370 . 13) (100 . "AcDbPolyline") (90 . 2) (70 . 0)
(43 . 0.0) (10 18631.221719457 3951.7349547511) (10 18634.9943438914 3925.3393665158))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18695.32239819 3891.4027149321 0.0) (10 18676.9367350139 3871.5429149111 0.0) (10 18639.1802061308
3886.8995210901 0.0) (10 18631.221719457 3910.2559954751 0.0))
((0 . "LWPOLYLINE") (100 . "AcDbEntity") (8 . "PLANTS") (62 . 94) (370 . 13) (100 . "AcDbPolyline") (90 . 2) (70 . 0)
(43 . 0.0) (10 18634.9943438914 3925.3393665158) (10 18631.221719457 3910.2559954751))
((0 . "LWPOLYLINE") (100 . "AcDbEntity") (8 . "PLANTS") (62 . 94) (370 . 13) (100 . "AcDbPolyline") (90 . 2) (70 . 0)
(43 . 0.0) (10 18631.221719457 1214.1770361991) (10 18650.0735294118 1187.7828054299))
((0 . "LWPOLYLINE") (100 . "AcDbEntity") (8 . "PLANTS") (62 . 94) (370 . 13) (100 . "AcDbPolyline") (90 . 3) (70 . 0)
(43 . 0.0) (10 18646.306561086 1240.5740950226) (10 18632.4259049774 1225.4892533937) (10 18631.221719457
1214.1770361991))
((0 . "LWPOLYLINE") (100 . "AcDbEntity") (8 . "PLANTS") (62 . 94) (370 . 13) (100 . "AcDbPolyline") (90 . 2) (70 . 0)
(43 . 0.0) (10 18691.5554298643 3936.6515837104) (10 18634.9943438914 3925.3393665158))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18638.7613122172 3763.1976244344 0.0) (10 18666.4140271502 3763.1975609269 0.0) (10 18694.0667420887
3763.1980504737 0.0) (10 18721.7194570136 3763.1971719457 0.0))
((0 . "LWPOLYLINE") (100 . "AcDbEntity") (8 . "PLANTS") (62 . 94) (370 . 13) (100 . "AcDbPolyline") (90 . 3) (70 . 0)
(43 . 0.0) (10 18638.7613122172 1157.6159502262) (10 18667.7309954751 1134.9915158371) (10 18676.4705882353
1104.8274886878))
((0 . "LWPOLYLINE") (100 . "AcDbEntity") (8 . "PLANTS") (62 . 94) (370 . 13) (100 . "AcDbPolyline") (90 . 2) (70 . 0)
(43 . 0.0) (10 18638.7613122172 1157.6159502262) (10 18650.0735294118 1187.7828054299))
((0 . "LWPOLYLINE") (100 . "AcDbEntity") (8 . "PLANTS") (62 . 94) (370 . 13) (100 . "AcDbPolyline") (90 . 2) (70 . 0)
(43 . 0.0) (10 18642.5339366516 4004.5248868778) (10 18657.6187782805 3989.4415158371))
((0 . "LWPOLYLINE") (100 . "AcDbEntity") (8 . "PLANTS") (62 . 94) (370 . 13) (100 . "AcDbPolyline") (90 . 2) (70 . 0)
(43 . 0.0) (10 18642.5339366516 4004.5248868778) (10 18646.306561086 4027.149321267))
((0 . "LWPOLYLINE") (100 . "AcDbEntity") (8 . "PLANTS") (62 . 94) (370 . 13) (100 . "AcDbPolyline") (90 . 3) (70 . 0)
(43 . 0.0) (10 18646.306561086 4027.149321267) (10 18624.9497737557 4056.4796380091) (10 18632.5275700795
4079.9845806382))
((0 . "LWPOLYLINE") (100 . "AcDbEntity") (8 . "PLANTS") (62 . 94) (370 . 13) (100 . "AcDbPolyline") (90 . 3) (70 . 0)
(43 . 0.0) (10 18691.5554298643 4030.9204751131) (10 18684.0061085973 4027.29739819) (10 18646.306561086
4027.149321267))
((0 . "LWPOLYLINE") (100 . "AcDbEntity") (8 . "PLANTS") (62 . 94) (370 . 13) (100 . "AcDbPolyline") (90 . 2) (70 . 0)
(43 . 0.0) (10 18646.3174535964 1242.4497370778) (10 18646.306561086 1240.5740950226))
((0 . "LWPOLYLINE") (100 . "AcDbEntity") (8 . "PLANTS") (62 . 94) (370 . 13) (100 . "AcDbPolyline") (90 . 2) (70 . 0)
(43 . 0.0) (10 18646.306561086 1240.5740950226) (10 18648.7496074249 1240.7776313207))
((0 . "LWPOLYLINE") (100 . "AcDbEntity") (8 . "PLANTS") (62 . 94) (370 . 13) (100 . "AcDbPolyline") (90 . 2) (70 . 0)
(43 . 0.0) (10 18695.32239819 1187.7828054299) (10 18650.0735294118 1187.7828054299))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18783.9366515837 3303.1674208145 0.0) (10 18780.0194506299 3266.7516127806 0.0) (10 18715.1194721193
3272.6305792554 0.0) (10 18698.7717356819 3278.3313391508 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18721.7194570136 3834.8416289593 0.0) (10 18703.7475109693 3820.9269329066 0.0) (10 18679.2599627783
3833.9120787758 0.0) (10 18661.3857466063 3819.7582579186 0.0))
((0 . "LWPOLYLINE") (100 . "AcDbEntity") (8 . "PLANTS") (62 . 94) (370 . 13) (100 . "AcDbPolyline") (90 . 2) (70 . 0)
(43 . 0.0) (10 18684.0101809955 840.8738687783) (10 18668.9309954751 806.9372171946))
((0 . "LWPOLYLINE") (100 . "AcDbEntity") (8 . "PLANTS") (62 . 94) (370 . 13) (100 . "AcDbPolyline") (90 . 3) (70 . 0)
(43 . 0.0) (10 18778.2805429864 1097.2850678733) (10 18733.0316742081 1097.4328054299) (10 18676.4705882353
1104.8274886878))
((0 . "LWPOLYLINE") (100 . "AcDbEntity") (8 . "PLANTS") (62 . 94) (370 . 13) (100 . "AcDbPolyline") (90 . 2) (70 . 0)
(43 . 0.0) (10 18695.32239819 3951.7349547511) (10 18680.2432126697 3959.2760180995))
((0 . "LWPOLYLINE") (100 . "AcDbEntity") (8 . "PLANTS") (62 . 94) (370 . 13) (100 . "AcDbPolyline") (90 . 2) (70 . 0)
(43 . 0.0) (10 18680.2432126697 3627.4505656109) (10 18699.0950226244 3634.9928733032))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18684.0101809955 840.8738687783 0.0) (10 18659.5450597529 884.2860819564 0.0) (10 18714.9876202183
895.0179390956 0.0) (10 18714.1798642534 931.3716063348 0.0))
((0 . "LWPOLYLINE") (100 . "AcDbEntity") (8 . "PLANTS") (62 . 94) (370 . 13) (100 . "AcDbPolyline") (90 . 2) (70 . 0)
(43 . 0.0) (10 18684.0101809955 840.8738687783) (10 18753.7726244344 846.5299773756))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.7811950597) (40
. 1) (40 . 1) (40 . 1) (40 . 1) (10 18754.1481900453 689.2912895927 0.0) (10 18719.2872986918 706.3331447208 0.0) (10
18696.046794472 675.5912942498 0.0) (10 18689.6581123163 641.1559034455 0.0) (10 18684.0101809956 637.2539592759 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18691.5554298643 4030.9204751131 0.0) (10 18707.9526017812 4029.9004226776 0.0) (10 18728.9176110685
4020.2073446882 0.0) (10 18744.3438914027 4030.9204751131 0.0))
((0 . "LWPOLYLINE") (100 . "AcDbEntity") (8 . "PLANTS") (62 . 94) (370 . 13) (100 . "AcDbPolyline") (90 . 2) (70 . 0)
(43 . 0.0) (10 18695.4116256126 4071.4206555159) (10 18691.5554298643 4030.9204751131))
((0 . "LWPOLYLINE") (100 . "AcDbEntity") (8 . "PLANTS") (62 . 94) (370 . 13) (100 . "AcDbPolyline") (90 . 2) (70 . 0)
(43 . 0.0) (10 18695.32239819 3891.4027149321) (10 18691.5554298643 3936.6515837104))
((0 . "LWPOLYLINE") (100 . "AcDbEntity") (8 . "PLANTS") (62 . 94) (370 . 13) (100 . "AcDbPolyline") (90 . 3) (70 . 0)
(43 . 0.0) (10 18695.32239819 3951.7349547511) (10 18691.5554298643 3947.963800905) (10 18691.5554298643
3936.6515837104))
((0 . "LWPOLYLINE") (100 . "AcDbEntity") (8 . "PLANTS") (62 . 94) (370 . 13) (100 . "AcDbPolyline") (90 . 2) (70 . 0)
(43 . 0.0) (10 18699.0950226244 3642.5339366516) (10 18691.5554298643 3650.075))
((0 . "LWPOLYLINE") (100 . "AcDbEntity") (8 . "PLANTS") (62 . 94) (370 . 13) (100 . "AcDbPolyline") (90 . 3) (70 . 0)
(43 . 0.0) (10 18695.32239819 1187.7828054299) (10 18698.9472850679 1217.9496606335) (10 18692.6977931806
1240.2648340939))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18793.3653846154 3940.4227375566 0.0) (10 18770.8840705147 3968.6297595614 0.0) (10 18724.516229503
3959.1075945915 0.0) (10 18695.32239819 3951.7349547511 0.0))
((0 . "LWPOLYLINE") (100 . "AcDbEntity") (8 . "PLANTS") (62 . 94) (370 . 13) (100 . "AcDbPolyline") (90 . 2) (70 . 0)
(43 . 0.0) (10 18710.407239819 3891.4027149321) (10 18695.32239819 3891.4027149321))
((0 . "LWPOLYLINE") (100 . "AcDbEntity") (8 . "PLANTS") (62 . 94) (370 . 13) (100 . "AcDbPolyline") (90 . 3) (70 . 0)
(43 . 0.0) (10 18695.32239819 1187.7828054299) (10 18702.871719457 1184.1600678733) (10 18725.492081448
1184.0130090498))
((0 . "LWPOLYLINE") (100 . "AcDbEntity") (8 . "PLANTS") (62 . 94) (370 . 13) (100 . "AcDbPolyline") (90 . 2) (70 . 0)
(43 . 0.0) (10 18729.2612980769 4110.1059954751) (10 18733.0316742081 4110.1059954751))
((0 . "LWPOLYLINE") (100 . "AcDbEntity") (8 . "PLANTS") (62 . 94) (370 . 13) (100 . "AcDbPolyline") (90 . 2) (70 . 0)
(43 . 0.0) (10 18699.0950226244 3642.5339366516) (10 18699.0950226244 3634.9928733032))
((0 . "LWPOLYLINE") (100 . "AcDbEntity") (8 . "PLANTS") (62 . 94) (370 . 13) (100 . "AcDbPolyline") (90 . 2) (70 . 0)
(43 . 0.0) (10 18699.0950226244 3642.5339366516) (10 18721.7194570136 3665.1583710407))
((0 . "LWPOLYLINE") (100 . "AcDbEntity") (8 . "PLANTS") (62 . 94) (370 . 13) (100 . "AcDbPolyline") (90 . 2) (70 . 0)
(43 . 0.0) (10 18717.9468325792 3616.1390271493) (10 18699.0950226244 3634.9928733032))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18759.4287330317 1134.9915158371 0.0) (10 18740.546927812 1141.3088501791 0.0) (10 18708.3757594318
1143.9046814624 0.0) (10 18702.8676470588 1168.9281674208 0.0))
((0 . "LWPOLYLINE") (100 . "AcDbEntity") (8 . "PLANTS") (62 . 94) (370 . 13) (100 . "AcDbPolyline") (90 . 2) (70 . 0)
(43 . 0.0) (10 18729.2590497738 761.6883484163) (10 18702.8676470588 742.8365384615))
((0 . "LWPOLYLINE") (100 . "AcDbEntity") (8 . "PLANTS") (62 . 94) (370 . 13) (100 . "AcDbPolyline") (90 . 2) (70 . 0)
(43 . 0.0) (10 18721.7194570136 3834.8416289593) (10 18710.407239819 3891.4027149321))
((0 . "LWPOLYLINE") (100 . "AcDbEntity") (8 . "PLANTS") (62 . 94) (370 . 13) (100 . "AcDbPolyline") (90 . 3) (70 . 0)
(43 . 0.0) (10 18710.407239819 3891.4027149321) (10 18717.9552036199 3895.0254524887) (10 18759.4287330317
3895.1738687783))
((0 . "LWPOLYLINE") (100 . "AcDbEntity") (8 . "PLANTS") (62 . 94) (370 . 13) (100 . "AcDbPolyline") (90 . 2) (70 . 0)
(43 . 0.0) (10 18725.492081448 935.1442307692) (10 18714.1798642534 931.3716063348))
((0 . "LWPOLYLINE") (100 . "AcDbEntity") (8 . "PLANTS") (62 . 94) (370 . 13) (100 . "AcDbPolyline") (90 . 3) (70 . 0)
(43 . 0.0) (10 18717.9468325792 3616.1390271493) (10 18718.096040724 3593.5208144796) (10 18721.7194570136
3585.9728506787))
((0 . "LWPOLYLINE") (100 . "AcDbEntity") (8 . "PLANTS") (62 . 94) (370 . 13) (100 . "AcDbPolyline") (90 . 2) (70 . 0)
(43 . 0.0) (10 18740.5712669683 3623.6806561086) (10 18717.9468325792 3616.1390271493))
((0 . "LWPOLYLINE") (100 . "AcDbEntity") (8 . "PLANTS") (62 . 94) (370 . 13) (100 . "AcDbPolyline") (90 . 2) (70 . 0)
(43 . 0.0) (10 18721.7194570136 3834.8416289593) (10 18748.1165158371 3831.0704751131))
((0 . "LWPOLYLINE") (100 . "AcDbEntity") (8 . "PLANTS") (62 . 94) (370 . 13) (100 . "AcDbPolyline") (90 . 2) (70 . 0)
(43 . 0.0) (10 18729.2590497738 3733.0316742081) (10 18721.7194570136 3763.1971719457))
((0 . "LWPOLYLINE") (100 . "AcDbEntity") (8 . "PLANTS") (62 . 94) (370 . 13) (100 . "AcDbPolyline") (90 . 2) (70 . 0)
(43 . 0.0) (10 18736.8042986425 3774.5093891403) (10 18721.7194570136 3763.1971719457))
((0 . "LWPOLYLINE") (100 . "AcDbEntity") (8 . "PLANTS") (62 . 94) (370 . 13) (100 . "AcDbPolyline") (90 . 2) (70 . 0)
(43 . 0.0) (10 18744.3438914027 3661.3872171946) (10 18721.7194570136 3665.1583710407))
((0 . "LWPOLYLINE") (100 . "AcDbEntity") (8 . "PLANTS") (62 . 94) (370 . 13) (100 . "AcDbPolyline") (90 . 3) (70 . 0)
(43 . 0.0) (10 18729.2590497738 3733.0316742081) (10 18721.8671945701 3691.553959276) (10 18721.7194570136
3665.1583710407))
((0 . "LWPOLYLINE") (100 . "AcDbEntity") (8 . "PLANTS") (62 . 94) (370 . 13) (100 . "AcDbPolyline") (90 . 2) (70 . 0)
(43 . 0.0) (10 18725.492081448 3567.1188914027) (10 18721.7194570136 3585.9728506787))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18759.4287330317 3623.6806561086 0.0) (10 18772.0555953072 3593.0618522468 0.0) (10 18741.8591427612
3581.2742850293 0.0) (10 18721.7194570136 3585.9728506787 0.0))
((0 . "LWPOLYLINE") (100 . "AcDbEntity") (8 . "PLANTS") (62 . 94) (370 . 13) (100 . "AcDbPolyline") (90 . 2) (70 . 0)
(43 . 0.0) (10 18721.7194570136 1018.0995475113) (10 18725.492081448 976.6204751131))
((0 . "LWPOLYLINE") (100 . "AcDbEntity") (8 . "PLANTS") (62 . 94) (370 . 13) (100 . "AcDbPolyline") (90 . 3) (70 . 0)
(43 . 0.0) (10 18778.2805429864 1097.2850678733) (10 18754.5997737557 1055.8059954751) (10 18721.7194570136
1018.0995475113))
((0 . "LWPOLYLINE") (100 . "AcDbEntity") (8 . "PLANTS") (62 . 94) (370 . 13) (100 . "AcDbPolyline") (90 . 2) (70 . 0)
(43 . 0.0) (10 18754.1481900452 689.2912895928) (10 18721.7194570136 659.8783936652))
((0 . "LWPOLYLINE") (100 . "AcDbEntity") (8 . "PLANTS") (62 . 94) (370 . 13) (100 . "AcDbPolyline") (90 . 2) (70 . 0)
(43 . 0.0) (10 18725.492081448 1202.8648190045) (10 18725.492081448 1184.0130090498))
((0 . "LWPOLYLINE") (100 . "AcDbEntity") (8 . "PLANTS") (62 . 94) (370 . 13) (100 . "AcDbPolyline") (90 . 2) (70 . 0)
(43 . 0.0) (10 18733.0316742081 1184.0130090498) (10 18725.492081448 1184.0130090498))
((0 . "LWPOLYLINE") (100 . "AcDbEntity") (8 . "PLANTS") (62 . 94) (370 . 13) (100 . "AcDbPolyline") (90 . 3) (70 . 0)
(43 . 0.0) (10 18763.1957013575 965.3082579186) (10 18744.3438914027 975.571719457) (10 18725.492081448 976.6204751131))
((0 . "LWPOLYLINE") (100 . "AcDbEntity") (8 . "PLANTS") (62 . 94) (370 . 13) (100 . "AcDbPolyline") (90 . 2) (70 . 0)
(43 . 0.0) (10 18725.492081448 965.3082579186) (10 18725.492081448 976.6204751131))
((0 . "LWPOLYLINE") (100 . "AcDbEntity") (8 . "PLANTS") (62 . 94) (370 . 13) (100 . "AcDbPolyline") (90 . 2) (70 . 0)
(43 . 0.0) (10 18725.492081448 935.1442307692) (10 18725.492081448 953.996040724))
((0 . "LWPOLYLINE") (100 . "AcDbEntity") (8 . "PLANTS") (62 . 94) (370 . 13) (100 . "AcDbPolyline") (90 . 2) (70 . 0)
(43 . 0.0) (10 18725.492081448 935.1442307692) (10 18763.1957013575 953.996040724))
((0 . "LWPOLYLINE") (100 . "AcDbEntity") (8 . "PLANTS") (62 . 94) (370 . 13) (100 . "AcDbPolyline") (90 . 2) (70 . 0)
(43 . 0.0) (10 18755.6561085973 625.9417420814) (10 18725.492081448 629.7143665158))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18729.2590497738 3733.0316742081 0.0) (10 18747.2773864358 3727.8710791339 0.0) (10 18755.7573824203
3754.8771079231 0.0) (10 18751.8834841629 3766.9683257919 0.0))
((0 . "LWPOLYLINE") (100 . "AcDbEntity") (8 . "PLANTS") (62 . 94) (370 . 13) (100 . "AcDbPolyline") (90 . 3) (70 . 0)
(43 . 0.0) (10 18729.2590497738 1259.4259049774) (10 18736.8083710407 1263.0501131222) (10 18759.4287330317
1263.1985294118))
((0 . "LWPOLYLINE") (100 . "AcDbEntity") (8 . "PLANTS") (62 . 94) (370 . 13) (100 . "AcDbPolyline") (90 . 2) (70 . 0)
(43 . 0.0) (10 18748.1165158371 757.9185520362) (10 18729.2590497738 761.6883484163))
((0 . "LWPOLYLINE") (100 . "AcDbEntity") (8 . "PLANTS") (62 . 94) (370 . 13) (100 . "AcDbPolyline") (90 . 3) (70 . 0)
(43 . 0.0) (10 18753.7726244344 846.5299773756) (10 18734.0811085973 791.8552036199) (10 18729.2590497738
761.6883484163))
((0 . "LWPOLYLINE") (100 . "AcDbEntity") (8 . "PLANTS") (62 . 94) (370 . 13) (100 . "AcDbPolyline") (90 . 2) (70 . 0)
(43 . 0.0) (10 18733.0316742081 4110.1059954751) (10 18744.3438914027 4087.481561086))
((0 . "LWPOLYLINE") (100 . "AcDbEntity") (8 . "PLANTS") (62 . 94) (370 . 13) (100 . "AcDbPolyline") (90 . 2) (70 . 0)
(43 . 0.0) (10 18733.0316742081 4110.1059954751) (10 18734.2974188246 4115.8615620439))
((0 . "LWPOLYLINE") (100 . "AcDbEntity") (8 . "PLANTS") (62 . 94) (370 . 13) (100 . "AcDbPolyline") (90 . 2) (70 . 0)
(43 . 0.0) (10 18736.8042986425 3774.5093891403) (10 18751.8834841629 3766.9683257919))
((0 . "LWPOLYLINE") (100 . "AcDbEntity") (8 . "PLANTS") (62 . 94) (370 . 13) (100 . "AcDbPolyline") (90 . 3) (70 . 0)
(43 . 0.0) (10 18736.8042986425 3774.5093891403) (10 18736.950678733 3797.1338235294) (10 18748.1165158371
3831.0704751131))
((0 . "LWPOLYLINE") (100 . "AcDbEntity") (8 . "PLANTS") (62 . 94) (370 . 13) (100 . "AcDbPolyline") (90 . 3) (70 . 0)
(43 . 0.0) (10 18736.8042986425 3476.6211538462) (10 18748.1165158371 3476.6211538462) (10 18751.8834841629
3472.850678733))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18748.1165158372 3438.9140271493 0.0) (10 18705.6941612175 3403.9565318393 0.0) (10 18697.3214138732
3479.1511784311 0.0) (10 18736.8042986426 3476.6211538462 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18793.3653846154 3540.7239819004 0.0) (10 18752.2242633901 3549.3093966674 0.0) (10 18731.1227536547
3509.945605614 0.0) (10 18736.8042986426 3476.6211538461 0.0))
((0 . "LWPOLYLINE") (100 . "AcDbEntity") (8 . "PLANTS") (62 . 94) (370 . 13) (100 . "AcDbPolyline") (90 . 2) (70 . 0)
(43 . 0.0) (10 18736.8042986425 882.3529411765) (10 18744.3438914027 882.3529411765))
((0 . "LWPOLYLINE") (100 . "AcDbEntity") (8 . "PLANTS") (62 . 94) (370 . 13) (100 . "AcDbPolyline") (90 . 2) (70 . 0)
(43 . 0.0) (10 18751.8834841629 509.0497737557) (10 18736.8042986425 512.8195701357))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18755.6561085973 595.7777149321 0.0) (10 18731.4539323168 576.8957032877 0.0) (10 18735.8646361431
538.5769931192 0.0) (10 18736.8042986425 512.8195701357 0.0))
((0 . "LWPOLYLINE") (100 . "AcDbEntity") (8 . "PLANTS") (62 . 94) (370 . 13) (100 . "AcDbPolyline") (90 . 2) (70 . 0)
(43 . 0.0) (10 18740.5712669683 3623.6806561086) (10 18759.4287330317 3623.6806561086))
((0 . "LWPOLYLINE") (100 . "AcDbEntity") (8 . "PLANTS") (62 . 94) (370 . 13) (100 . "AcDbPolyline") (90 . 2) (70 . 0)
(43 . 0.0) (10 18740.5712669683 3623.6806561086) (10 18744.3438914027 3661.3872171946))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18740.5712669683 3378.5824660633 0.0) (10 18722.6045650908 3409.0105885681 0.0) (10 18772.9058802495
3402.0486035512 0.0) (10 18782.0531674208 3420.0600678733 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18751.8834841629 509.0497737557 0.0) (10 18746.4168345909 500.5043847882 0.0) (10 18758.8733072665
468.8251242391 0.0) (10 18740.5712669683 463.8009049774 0.0))
((0 . "LWPOLYLINE") (100 . "AcDbEntity") (8 . "PLANTS") (62 . 94) (370 . 13) (100 . "AcDbPolyline") (90 . 3) (70 . 0)
(43 . 0.0) (10 18744.3438914027 4087.481561086) (10 18737.0984162896 4061.0859728507) (10 18744.3438914027
4030.9204751131))
((0 . "LWPOLYLINE") (100 . "AcDbEntity") (8 . "PLANTS") (62 . 94) (370 . 13) (100 . "AcDbPolyline") (90 . 2) (70 . 0)
(43 . 0.0) (10 18770.7409502262 4095.0226244344) (10 18744.3438914027 4087.481561086))
((0 . "LWPOLYLINE") (100 . "AcDbEntity") (8 . "PLANTS") (62 . 94) (370 . 13) (100 . "AcDbPolyline") (90 . 2) (70 . 0)
(43 . 0.0) (10 18744.3438914027 4030.9204751131) (10 18819.7567873303 3993.2126696833))
((0 . "LWPOLYLINE") (100 . "AcDbEntity") (8 . "PLANTS") (62 . 94) (370 . 13) (100 . "AcDbPolyline") (90 . 3) (70 . 0)
(43 . 0.0) (10 18759.4287330317 3665.1583710407) (10 18748.1165158371 3665.1583710407) (10 18744.3438914027
3661.3872171946))
((0 . "LWPOLYLINE") (100 . "AcDbEntity") (8 . "PLANTS") (62 . 94) (370 . 13) (100 . "AcDbPolyline") (90 . 2) (70 . 0)
(43 . 0.0) (10 18759.4287330317 1134.9915158371) (10 18744.3438914027 1165.1583710407))
((0 . "LWPOLYLINE") (100 . "AcDbEntity") (8 . "PLANTS") (62 . 94) (370 . 13) (100 . "AcDbPolyline") (90 . 2) (70 . 0)
(43 . 0.0) (10 18753.7726244344 846.5299773756) (10 18744.3438914027 882.3529411765))
((0 . "LWPOLYLINE") (100 . "AcDbEntity") (8 . "PLANTS") (62 . 94) (370 . 13) (100 . "AcDbPolyline") (90 . 2) (70 . 0)
(43 . 0.0) (10 18744.3438914027 882.3529411765) (10 18774.507918552 893.665158371))
((0 . "LWPOLYLINE") (100 . "AcDbEntity") (8 . "PLANTS") (62 . 94) (370 . 13) (100 . "AcDbPolyline") (90 . 2) (70 . 0)
(43 . 0.0) (10 18763.1957013575 3831.0704751131) (10 18748.1165158371 3831.0704751131))
((0 . "LWPOLYLINE") (100 . "AcDbEntity") (8 . "PLANTS") (62 . 94) (370 . 13) (100 . "AcDbPolyline") (90 . 3) (70 . 0)
(43 . 0.0) (10 18748.1165158371 3438.9140271493) (10 18766.9683257919 3437.709841629) (10 18782.0531674208
3427.6018099548))
((0 . "LWPOLYLINE") (100 . "AcDbEntity") (8 . "PLANTS") (62 . 94) (370 . 13) (100 . "AcDbPolyline") (90 . 2) (70 . 0)
(43 . 0.0) (10 18748.1165158371 3438.9140271493) (10 18751.8834841629 3472.850678733))
((0 . "LWPOLYLINE") (100 . "AcDbEntity") (8 . "PLANTS") (62 . 94) (370 . 13) (100 . "AcDbPolyline") (90 . 2) (70 . 0)
(43 . 0.0) (10 18754.1481900452 689.2912895928) (10 18748.1165158371 757.9185520362))
((0 . "LWPOLYLINE") (100 . "AcDbEntity") (8 . "PLANTS") (62 . 94) (370 . 13) (100 . "AcDbPolyline") (90 . 2) (70 . 0)
(43 . 0.0) (10 18770.7409502262 765.4609728507) (10 18748.1165158371 757.9185520362))
((0 . "LWPOLYLINE") (100 . "AcDbEntity") (8 . "PLANTS") (62 . 94) (370 . 13) (100 . "AcDbPolyline") (90 . 2) (70 . 0)
(43 . 0.0) (10 18763.1957013575 4140.2714932127) (10 18757.3587422676 4142.2173602645))
((0 . "LWPOLYLINE") (100 . "AcDbEntity") (8 . "PLANTS") (62 . 94) (370 . 13) (100 . "AcDbPolyline") (90 . 3) (70 . 0)
(43 . 0.0) (10 18804.67760181 3759.4272624434) (10 18785.8201357466 3766.8202488688) (10 18751.8834841629
3766.9683257919))
((0 . "LWPOLYLINE") (100 . "AcDbEntity") (8 . "PLANTS") (62 . 94) (370 . 13) (100 . "AcDbPolyline") (90 . 2) (70 . 0)
(43 . 0.0) (10 18797.1323529412 3476.6211538462) (10 18751.8834841629 3472.850678733))
((0 . "LWPOLYLINE") (100 . "AcDbEntity") (8 . "PLANTS") (62 . 94) (370 . 13) (100 . "AcDbPolyline") (90 . 3) (70 . 0)
(43 . 0.0) (10 18759.4287330317 1263.1985294118) (10 18766.8205882353 1293.3625565611) (10 18766.8205882353
1324.9765998707))
((0 . "LWPOLYLINE") (100 . "AcDbEntity") (8 . "PLANTS") (62 . 94) (370 . 13) (100 . "AcDbPolyline") (90 . 2) (70 . 0)
(43 . 0.0) (10 18782.0531674208 509.0497737557) (10 18751.8834841629 509.0497737557))
((0 . "LWPOLYLINE") (100 . "AcDbEntity") (8 . "PLANTS") (62 . 94) (370 . 13) (100 . "AcDbPolyline") (90 . 2) (70 . 0)
(43 . 0.0) (10 18753.7726244344 846.5299773756) (10 18782.0531674208 852.1860859729))
((0 . "LWPOLYLINE") (100 . "AcDbEntity") (8 . "PLANTS") (62 . 94) (370 . 13) (100 . "AcDbPolyline") (90 . 3) (70 . 0)
(43 . 0.0) (10 18766.9683257919 625.9417420814) (10 18766.8205882353 667.4208144796) (10 18754.1481900452
689.2912895928))
((0 . "LWPOLYLINE") (100 . "AcDbEntity") (8 . "PLANTS") (62 . 94) (370 . 13) (100 . "AcDbPolyline") (90 . 3) (70 . 0)
(43 . 0.0) (10 18785.8201357466 701.3574660633) (10 18763.1433257919 696.3662895928) (10 18754.1481900452
689.2912895928))
((0 . "LWPOLYLINE") (100 . "AcDbEntity") (8 . "PLANTS") (62 . 94) (370 . 13) (100 . "AcDbPolyline") (90 . 2) (70 . 0)
(43 . 0.0) (10 18766.9683257919 625.9417420814) (10 18755.6561085973 625.9417420814))
((0 . "LWPOLYLINE") (100 . "AcDbEntity") (8 . "PLANTS") (62 . 94) (370 . 13) (100 . "AcDbPolyline") (90 . 2) (70 . 0)
(43 . 0.0) (10 18755.6561085973 625.9417420814) (10 18755.6561085973 595.7777149321))
((0 . "LWPOLYLINE") (100 . "AcDbEntity") (8 . "PLANTS") (62 . 94) (370 . 13) (100 . "AcDbPolyline") (90 . 2) (70 . 0)
(43 . 0.0) (10 18755.6561085973 595.7777149321) (10 18789.592760181 599.5475113122))
((0 . "LWPOLYLINE") (100 . "AcDbEntity") (8 . "PLANTS") (62 . 94) (370 . 13) (100 . "AcDbPolyline") (90 . 2) (70 . 0)
(43 . 0.0) (10 18770.7409502262 3880.0904977376) (10 18759.4287330317 3895.1738687783))
((0 . "LWPOLYLINE") (100 . "AcDbEntity") (8 . "PLANTS") (62 . 94) (370 . 13) (100 . "AcDbPolyline") (90 . 3) (70 . 0)
(43 . 0.0) (10 18793.3653846154 3940.4227375566) (10 18768.0246606335 3917.7914027149) (10 18759.4287330317
3895.1738687783))
((0 . "LWPOLYLINE") (100 . "AcDbEntity") (8 . "PLANTS") (62 . 94) (370 . 13) (100 . "AcDbPolyline") (90 . 2) (70 . 0)
(43 . 0.0) (10 18759.4287330317 3665.1583710407) (10 18778.2805429864 3653.8461538462))
((0 . "LWPOLYLINE") (100 . "AcDbEntity") (8 . "PLANTS") (62 . 94) (370 . 13) (100 . "AcDbPolyline") (90 . 3) (70 . 0)
(43 . 0.0) (10 18759.4287330317 3665.1583710407) (10 18764.2535067873 3680.2417420814) (10 18782.0531674208
3695.3238687783))
((0 . "LWPOLYLINE") (100 . "AcDbEntity") (8 . "PLANTS") (62 . 94) (370 . 13) (100 . "AcDbPolyline") (90 . 2) (70 . 0)
(43 . 0.0) (10 18759.4287330317 3623.6806561086) (10 18778.2805429864 3627.4505656109))
((0 . "LWPOLYLINE") (100 . "AcDbEntity") (8 . "PLANTS") (62 . 94) (370 . 13) (100 . "AcDbPolyline") (90 . 3) (70 . 0)
(43 . 0.0) (10 18806.5610859729 1210.407239819) (10 18778.428280543 1225.6376696833) (10 18759.4287330317
1263.1985294118))
((0 . "LWPOLYLINE") (100 . "AcDbEntity") (8 . "PLANTS") (62 . 94) (370 . 13) (100 . "AcDbPolyline") (90 . 3) (70 . 0)
(43 . 0.0) (10 18759.4287330317 1134.9915158371) (10 18766.9752262443 1133.7881221719) (10 18789.592760181
1116.1397058824))
((0 . "LWPOLYLINE") (100 . "AcDbEntity") (8 . "PLANTS") (62 . 94) (370 . 13) (100 . "AcDbPolyline") (90 . 2) (70 . 0)
(43 . 0.0) (10 18763.1957013575 4140.2714932127) (10 18800.9049773756 4132.7304298643))
((0 . "LWPOLYLINE") (100 . "AcDbEntity") (8 . "PLANTS") (62 . 94) (370 . 13) (100 . "AcDbPolyline") (90 . 2) (70 . 0)
(43 . 0.0) (10 18770.7409502262 4095.0226244344) (10 18763.1957013575 4140.2714932127))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18763.1957013575 3831.0704751131 0.0) (10 18783.9696066544 3792.2226759326 0.0) (10 18845.7564054296
3808.083970007 0.0) (10 18876.3178733032 3823.5294117647 0.0))
((0 . "LWPOLYLINE") (100 . "AcDbEntity") (8 . "PLANTS") (62 . 94) (370 . 13) (100 . "AcDbPolyline") (90 . 3) (70 . 0)
(43 . 0.0) (10 18770.7409502262 3880.0904977376) (10 18770.5917420815 3857.4660633484) (10 18763.1957013575
3831.0704751131))
((0 . "LWPOLYLINE") (100 . "AcDbEntity") (8 . "PLANTS") (62 . 94) (370 . 13) (100 . "AcDbPolyline") (90 . 2) (70 . 0)
(43 . 0.0) (10 18763.1957013575 953.996040724) (10 18763.1957013575 965.3082579186))
((0 . "LWPOLYLINE") (100 . "AcDbEntity") (8 . "PLANTS") (62 . 94) (370 . 13) (100 . "AcDbPolyline") (90 . 2) (70 . 0)
(43 . 0.0) (10 18766.9683257919 972.850678733) (10 18763.1957013575 965.3082579186))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18763.1957013575 953.996040724 0.0) (10 18776.158479221 937.9481289241 0.0) (10 18783.2898480864
913.0736071493 0.0) (10 18774.507918552 893.665158371 0.0))
((0 . "LWPOLYLINE") (100 . "AcDbEntity") (8 . "PLANTS") (62 . 94) (370 . 13) (100 . "AcDbPolyline") (90 . 2) (70 . 0)
(43 . 0.0) (10 18763.1957013575 384.6153846154) (10 18763.1957013575 392.1578054299))
((0 . "LWPOLYLINE") (100 . "AcDbEntity") (8 . "PLANTS") (62 . 94) (370 . 13) (100 . "AcDbPolyline") (90 . 2) (70 . 0)
(43 . 0.0) (10 18766.9683257919 972.850678733) (10 18770.7409502262 995.4751131222))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18766.9683257918 972.850678733 0.0) (10 18800.8277085475 989.0614093445 0.0) (10 18824.7166394232
949.4701359704 0.0) (10 18857.4660633484 950.2262443439 0.0))
((0 . "LWPOLYLINE") (100 . "AcDbEntity") (8 . "PLANTS") (62 . 94) (370 . 13) (100 . "AcDbPolyline") (90 . 3) (70 . 0)
(43 . 0.0) (10 18766.9683257919 625.9417420814) (10 18788.3885746606 622.0173076923) (10 18789.592760181
599.5475113122))
((0 . "LWPOLYLINE") (100 . "AcDbEntity") (8 . "PLANTS") (62 . 94) (370 . 13) (100 . "AcDbPolyline") (90 . 2) (70 . 0)
(43 . 0.0) (10 18770.7409502262 4095.0226244344) (10 18778.2805429864 4095.0226244344))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18770.7409502262 3880.0904977376 0.0) (10 18810.8278061535 3871.6847636831 0.0) (10 18795.7031822567
3913.099011858 0.0) (10 18815.9898190045 3925.3393665158 0.0))
((0 . "LWPOLYLINE") (100 . "AcDbEntity") (8 . "PLANTS") (62 . 94) (370 . 13) (100 . "AcDbPolyline") (90 . 3) (70 . 0)
(43 . 0.0) (10 18770.7409502262 765.4609728507) (10 18778.290158371 761.8395927602) (10 18791.4762443439
763.5746606335))
((0 . "LWPOLYLINE") (100 . "AcDbEntity") (8 . "PLANTS") (62 . 94) (370 . 13) (100 . "AcDbPolyline") (90 . 3) (70 . 0)
(43 . 0.0) (10 18785.8201357466 795.625) (10 18771.9436651584 788.0778280543) (10 18770.7409502262 765.4609728507))
((0 . "LWPOLYLINE") (100 . "AcDbEntity") (8 . "PLANTS") (62 . 94) (370 . 13) (100 . "AcDbPolyline") (90 . 3) (70 . 0)
(43 . 0.0) (10 18782.0531674208 852.1860859729) (10 18781.8970588235 882.3529411765) (10 18774.507918552 893.665158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18812.2171945701 4068.6270361991 0.0) (10 18796.2941178013 4066.4630253861 0.0) (10 18781.8217578974
4080.1903080609 0.0) (10 18778.2805429864 4095.0226244344 0.0))
((0 . "LWPOLYLINE") (100 . "AcDbEntity") (8 . "PLANTS") (62 . 94) (370 . 13) (100 . "AcDbPolyline") (90 . 3) (70 . 0)
(43 . 0.0) (10 18800.9049773756 4132.7304298643) (10 18792.3075791855 4110.1059954751) (10 18778.2805429864
4095.0226244344))
((0 . "LWPOLYLINE") (100 . "AcDbEntity") (8 . "PLANTS") (62 . 94) (370 . 13) (100 . "AcDbPolyline") (90 . 2) (70 . 0)
(43 . 0.0) (10 18778.2805429864 3653.8461538462) (10 18778.2805429864 3627.4505656109))
((0 . "LWPOLYLINE") (100 . "AcDbEntity") (8 . "PLANTS") (62 . 94) (370 . 13) (100 . "AcDbPolyline") (90 . 3) (70 . 0)
(43 . 0.0) (10 18793.3653846154 3672.6994343891) (10 18789.439479638 3661.3941176471) (10 18778.2805429864
3653.8461538462))
((0 . "LWPOLYLINE") (100 . "AcDbEntity") (8 . "PLANTS") (62 . 94) (370 . 13) (100 . "AcDbPolyline") (90 . 2) (70 . 0)
(43 . 0.0) (10 18778.2805429864 3627.4505656109) (10 18812.2171945701 3623.6806561086))
((0 . "LWPOLYLINE") (100 . "AcDbEntity") (8 . "PLANTS") (62 . 94) (370 . 13) (100 . "AcDbPolyline") (90 . 2) (70 . 0)
(43 . 0.0) (10 18778.2805429864 1097.2850678733) (10 18789.592760181 1104.8274886878))
((0 . "LWPOLYLINE") (100 . "AcDbEntity") (8 . "PLANTS") (62 . 94) (370 . 13) (100 . "AcDbPolyline") (90 . 2) (70 . 0)
(43 . 0.0) (10 18793.3653846154 3672.6994343891) (10 18782.0531674208 3695.3238687783))
((0 . "LWPOLYLINE") (100 . "AcDbEntity") (8 . "PLANTS") (62 . 94) (370 . 13) (100 . "AcDbPolyline") (90 . 3) (70 . 0)
(43 . 0.0) (10 18782.0531674208 3695.3238687783) (10 18787.0201357466 3717.9483031674) (10 18800.9049773756
3729.260520362))
((0 . "LWPOLYLINE") (100 . "AcDbEntity") (8 . "PLANTS") (62 . 94) (370 . 13) (100 . "AcDbPolyline") (90 . 2) (70 . 0)
(43 . 0.0) (10 18782.0531674208 3427.6018099548) (10 18782.0531674208 3420.0600678733))
((0 . "LWPOLYLINE") (100 . "AcDbEntity") (8 . "PLANTS") (62 . 94) (370 . 13) (100 . "AcDbPolyline") (90 . 2) (70 . 0)
(43 . 0.0) (10 18782.0531674208 3427.6018099548) (10 18804.67760181 3438.9140271493))
((0 . "LWPOLYLINE") (100 . "AcDbEntity") (8 . "PLANTS") (62 . 94) (370 . 13) (100 . "AcDbPolyline") (90 . 3) (70 . 0)
(43 . 0.0) (10 18812.2171945701 3408.7478506787) (10 18793.3653846154 3409.9520361991) (10 18782.0531674208
3420.0600678733))
((0 . "LWPOLYLINE") (100 . "AcDbEntity") (8 . "PLANTS") (62 . 94) (370 . 13) (100 . "AcDbPolyline") (90 . 3) (70 . 0)
(43 . 0.0) (10 18783.9366515837 3303.1674208145) (10 18785.6737556561 3318.2501131222) (10 18782.0531674208
3329.5623303167))
((0 . "LWPOLYLINE") (100 . "AcDbEntity") (8 . "PLANTS") (62 . 94) (370 . 13) (100 . "AcDbPolyline") (90 . 2) (70 . 0)
(43 . 0.0) (10 18782.0531674208 852.1860859729) (10 18797.1323529412 852.1860859729))
((0 . "LWPOLYLINE") (100 . "AcDbEntity") (8 . "PLANTS") (62 . 94) (370 . 13) (100 . "AcDbPolyline") (90 . 2) (70 . 0)
(43 . 0.0) (10 18782.0531674208 509.0497737557) (10 18789.592760181 509.0497737557))
((0 . "LWPOLYLINE") (100 . "AcDbEntity") (8 . "PLANTS") (62 . 94) (370 . 13) (100 . "AcDbPolyline") (90 . 2) (70 . 0)
(43 . 0.0) (10 18782.0531674208 509.0497737557) (10 18789.592760181 460.0311085973))
((0 . "LWPOLYLINE") (100 . "AcDbEntity") (8 . "PLANTS") (62 . 94) (370 . 13) (100 . "AcDbPolyline") (90 . 3) (70 . 0)
(43 . 0.0) (10 18783.9366515837 3303.1674208145) (10 18823.5294117647 3306.7832579186) (10 18834.8416289593
3299.3969457014))
((0 . "LWPOLYLINE") (100 . "AcDbEntity") (8 . "PLANTS") (62 . 94) (370 . 13) (100 . "AcDbPolyline") (90 . 3) (70 . 0)
(43 . 0.0) (10 18785.8201357466 795.625) (10 18793.2092760181 784.3127828054) (10 18791.4762443439 763.5746606335))
((0 . "LWPOLYLINE") (100 . "AcDbEntity") (8 . "PLANTS") (62 . 94) (370 . 13) (100 . "AcDbPolyline") (90 . 2) (70 . 0)
(43 . 0.0) (10 18785.8201357466 795.625) (10 18804.67760181 822.0220588235))
((0 . "LWPOLYLINE") (100 . "AcDbEntity") (8 . "PLANTS") (62 . 94) (370 . 13) (100 . "AcDbPolyline") (90 . 2) (70 . 0)
(43 . 0.0) (10 18785.8201357466 701.3574660633) (10 18800.9049773756 693.8150452489))
((0 . "LWPOLYLINE") (100 . "AcDbEntity") (8 . "PLANTS") (62 . 94) (370 . 13) (100 . "AcDbPolyline") (90 . 2) (70 . 0)
(43 . 0.0) (10 18785.8201357466 701.3574660633) (10 18791.4762443439 763.5746606335))
((0 . "LWPOLYLINE") (100 . "AcDbEntity") (8 . "PLANTS") (62 . 94) (370 . 13) (100 . "AcDbPolyline") (90 . 2) (70 . 0)
(43 . 0.0) (10 18789.592760181 3359.7285067873) (10 18800.9049773756 3363.4989819005))
((0 . "LWPOLYLINE") (100 . "AcDbEntity") (8 . "PLANTS") (62 . 94) (370 . 13) (100 . "AcDbPolyline") (90 . 2) (70 . 0)
(43 . 0.0) (10 18789.592760181 1104.8274886878) (10 18789.592760181 1116.1397058824))
((0 . "LWPOLYLINE") (100 . "AcDbEntity") (8 . "PLANTS") (62 . 94) (370 . 13) (100 . "AcDbPolyline") (90 . 2) (70 . 0)
(43 . 0.0) (10 18797.1323529412 1127.4519230769) (10 18789.592760181 1116.1397058824))
((0 . "LWPOLYLINE") (100 . "AcDbEntity") (8 . "PLANTS") (62 . 94) (370 . 13) (100 . "AcDbPolyline") (90 . 3) (70 . 0)
(43 . 0.0) (10 18808.4445701357 1093.5152714932) (10 18800.8980769231 1094.7186651584) (10 18789.592760181
1104.8274886878))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18789.592760181 509.0497737557 0.0) (10 18770.5835952785 542.670549236 0.0) (10 18817.8025166386
567.2960032366 0.0) (10 18789.592760181 599.5475113122 0.0))
((0 . "LWPOLYLINE") (100 . "AcDbEntity") (8 . "PLANTS") (62 . 94) (370 . 13) (100 . "AcDbPolyline") (90 . 3) (70 . 0)
(43 . 0.0) (10 18897.4371667753 512.5187812937) (10 18861.2386877828 505.284841629) (10 18789.592760181 509.0497737557))
((0 . "LWPOLYLINE") (100 . "AcDbEntity") (8 . "PLANTS") (62 . 94) (370 . 13) (100 . "AcDbPolyline") (90 . 2) (70 . 0)
(43 . 0.0) (10 18791.4762443439 763.5746606335) (10 18853.693438914 765.4609728507))
((0 . "LWPOLYLINE") (100 . "AcDbEntity") (8 . "PLANTS") (62 . 94) (370 . 13) (100 . "AcDbPolyline") (90 . 2) (70 . 0)
(43 . 0.0) (10 18793.3653846154 3940.4227375566) (10 18814.100678733 3940.4227375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18793.3653846154 3672.6994343891 0.0) (10 18829.8129508108 3662.0298799617 0.0) (10 18821.7861965459
3718.7106793154 0.0) (10 18800.9049773756 3729.260520362 0.0))
((0 . "LWPOLYLINE") (100 . "AcDbEntity") (8 . "PLANTS") (62 . 94) (370 . 13) (100 . "AcDbPolyline") (90 . 3) (70 . 0)
(43 . 0.0) (10 18793.3653846154 3540.7239819005) (10 18802.0952488688 3518.2541855204) (10 18808.4445701357
3514.3290723982))
((0 . "LWPOLYLINE") (100 . "AcDbEntity") (8 . "PLANTS") (62 . 94) (370 . 13) (100 . "AcDbPolyline") (90 . 2) (70 . 0)
(43 . 0.0) (10 18793.3653846154 3540.7239819005) (10 18812.2171945701 3548.2657239819))
((0 . "LWPOLYLINE") (100 . "AcDbEntity") (8 . "PLANTS") (62 . 94) (370 . 13) (100 . "AcDbPolyline") (90 . 2) (70 . 0)
(43 . 0.0) (10 18797.1323529412 3476.6211538462) (10 18804.67760181 3438.9140271493))
((0 . "LWPOLYLINE") (100 . "AcDbEntity") (8 . "PLANTS") (62 . 94) (370 . 13) (100 . "AcDbPolyline") (90 . 2) (70 . 0)
(43 . 0.0) (10 18797.1323529412 3476.6211538462) (10 18808.4445701357 3484.1628959276))
((0 . "LWPOLYLINE") (100 . "AcDbEntity") (8 . "PLANTS") (62 . 94) (370 . 13) (100 . "AcDbPolyline") (90 . 3) (70 . 0)
(43 . 0.0) (10 18806.5610859729 1210.407239819) (10 18801.0527149321 1195.3252262443) (10 18797.1323529412
1127.4519230769))
((0 . "LWPOLYLINE") (100 . "AcDbEntity") (8 . "PLANTS") (62 . 94) (370 . 13) (100 . "AcDbPolyline") (90 . 3) (70 . 0)
(43 . 0.0) (10 18797.1323529412 1127.4519230769) (10 18815.9898190045 1134.8382352941) (10 18838.6142533937
1134.9915158371))
((0 . "LWPOLYLINE") (100 . "AcDbEntity") (8 . "PLANTS") (62 . 94) (370 . 13) (100 . "AcDbPolyline") (90 . 2) (70 . 0)
(43 . 0.0) (10 18797.1323529412 852.1860859729) (10 18804.67760181 822.0220588235))
((0 . "LWPOLYLINE") (100 . "AcDbEntity") (8 . "PLANTS") (62 . 94) (370 . 13) (100 . "AcDbPolyline") (90 . 3) (70 . 0)
(43 . 0.0) (10 18842.3812217195 878.5831447964) (10 18812.2171945701 866.213800905) (10 18797.1323529412
852.1860859729))
((0 . "LWPOLYLINE") (100 . "AcDbEntity") (8 . "PLANTS") (62 . 94) (370 . 13) (100 . "AcDbPolyline") (90 . 3) (70 . 0)
(43 . 0.0) (10 18800.9049773756 4132.7304298643) (10 18804.67760181 4132.7304298643) (10 18812.2171945701
4144.0426470588))
((0 . "LWPOLYLINE") (100 . "AcDbEntity") (8 . "PLANTS") (62 . 94) (370 . 13) (100 . "AcDbPolyline") (90 . 2) (70 . 0)
(43 . 0.0) (10 18804.67760181 3759.4272624434) (10 18800.9049773756 3729.260520362))
((0 . "LWPOLYLINE") (100 . "AcDbEntity") (8 . "PLANTS") (62 . 94) (370 . 13) (100 . "AcDbPolyline") (90 . 3) (70 . 0)
(43 . 0.0) (10 18800.9049773756 3363.4989819005) (10 18812.2171945701 3355.9580316742) (10 18812.2171945701
3352.1867647059))
((0 . "LWPOLYLINE") (100 . "AcDbEntity") (8 . "PLANTS") (62 . 94) (370 . 13) (100 . "AcDbPolyline") (90 . 2) (70 . 0)
(43 . 0.0) (10 18800.9049773756 3363.4989819005) (10 18815.9898190045 3386.1234162896))
((0 . "LWPOLYLINE") (100 . "AcDbEntity") (8 . "PLANTS") (62 . 94) (370 . 13) (100 . "AcDbPolyline") (90 . 3) (70 . 0)
(43 . 0.0) (10 18804.67760181 3759.4272624434) (10 18853.6893665158 3759.2788461538) (10 18861.2386877828
3755.6561085973))
((0 . "LWPOLYLINE") (100 . "AcDbEntity") (8 . "PLANTS") (62 . 94) (370 . 13) (100 . "AcDbPolyline") (90 . 3) (70 . 0)
(43 . 0.0) (10 18812.2171945701 3408.7478506787) (10 18814.9320135747 3423.8313348416) (10 18804.67760181
3438.9140271493))
((0 . "LWPOLYLINE") (100 . "AcDbEntity") (8 . "PLANTS") (62 . 94) (370 . 13) (100 . "AcDbPolyline") (90 . 3) (70 . 0)
(43 . 0.0) (10 18834.8416289593 3299.3969457014) (10 18808.600678733 3273.0012443439) (10 18804.67760181
3257.9185520362))
((0 . "LWPOLYLINE") (100 . "AcDbEntity") (8 . "PLANTS") (62 . 94) (370 . 13) (100 . "AcDbPolyline") (90 . 2) (70 . 0)
(43 . 0.0) (10 18804.67760181 822.0220588235) (10 18849.9264705882 818.2494343891))
((0 . "LWPOLYLINE") (100 . "AcDbEntity") (8 . "PLANTS") (62 . 94) (370 . 13) (100 . "AcDbPolyline") (90 . 3) (70 . 0)
(43 . 0.0) (10 18806.5610859729 1210.407239819) (10 18819.7554298643 1203.0201357466) (10 18857.4660633484
1199.0950226244))
((0 . "LWPOLYLINE") (100 . "AcDbEntity") (8 . "PLANTS") (62 . 94) (370 . 13) (100 . "AcDbPolyline") (90 . 3) (70 . 0)
(43 . 0.0) (10 18806.5610859729 1210.407239819) (10 18812.0652714932 1221.7194570136) (10 18812.2171945701
1240.5740950226))
((0 . "LWPOLYLINE") (100 . "AcDbEntity") (8 . "PLANTS") (62 . 94) (370 . 13) (100 . "AcDbPolyline") (90 . 2) (70 . 0)
(43 . 0.0) (10 18808.4445701357 3514.3290723982) (10 18808.4445701357 3484.1628959276))
((0 . "LWPOLYLINE") (100 . "AcDbEntity") (8 . "PLANTS") (62 . 94) (370 . 13) (100 . "AcDbPolyline") (90 . 3) (70 . 0)
(43 . 0.0) (10 18808.4445701357 3514.3290723982) (10 18830.9157239819 3533.182239819) (10 18834.8416289593
3544.4944570136))
((0 . "LWPOLYLINE") (100 . "AcDbEntity") (8 . "PLANTS") (62 . 94) (370 . 13) (100 . "AcDbPolyline") (90 . 2) (70 . 0)
(43 . 0.0) (10 18849.9264705882 3472.850678733) (10 18808.4445701357 3484.1628959276))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2846103807)
(40 . 0.4530991864) (40 . 1) (40 . 1) (40 . 1) (40 . 1) (10 18808.4445701357 1093.5152714932 0.0) (10 18823.1455374582
1078.5184040294 0.0) (10 18810.5363105491 1056.5468560797 0.0) (10 18769.421203371 1016.2430947705 0.0) (10
18851.8134761132 998.1941325652 0.0) (10 18861.2386877828 1014.3297511312 0.0))
((0 . "LWPOLYLINE") (100 . "AcDbEntity") (8 . "PLANTS") (62 . 94) (370 . 13) (100 . "AcDbPolyline") (90 . 2) (70 . 0)
(43 . 0.0) (10 18808.4445701357 1093.5152714932) (10 18838.6142533937 1108.5972850679))
((0 . "LWPOLYLINE") (100 . "AcDbEntity") (8 . "PLANTS") (62 . 94) (370 . 13) (100 . "AcDbPolyline") (90 . 2) (70 . 0)
(43 . 0.0) (10 18812.2171945701 4144.0426470588) (10 18861.2386877828 4144.0426470588))
((0 . "LWPOLYLINE") (100 . "AcDbEntity") (8 . "PLANTS") (62 . 94) (370 . 13) (100 . "AcDbPolyline") (90 . 2) (70 . 0)
(43 . 0.0) (10 18812.2171945701 4144.0426470588) (10 18812.2156893096 4204.9110140268))
((0 . "LWPOLYLINE") (100 . "AcDbEntity") (8 . "PLANTS") (62 . 94) (370 . 13) (100 . "AcDbPolyline") (90 . 2) (70 . 0)
(43 . 0.0) (10 18812.2171945701 4057.3148190045) (10 18812.2171945701 4068.6270361991))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18812.2171945701 4068.6270361991 0.0) (10 18813.1730160214 4094.2151785521 0.0) (10 18852.7127160756
4098.1894417805 0.0) (10 18849.9264705882 4068.6270361991 0.0))
((0 . "LWPOLYLINE") (100 . "AcDbEntity") (8 . "PLANTS") (62 . 94) (370 . 13) (100 . "AcDbPolyline") (90 . 3) (70 . 0)
(43 . 0.0) (10 18812.2171945701 4057.3148190045) (10 18827.3020361991 4057.1608597285) (10 18842.3812217195
4049.7737556561))
((0 . "LWPOLYLINE") (100 . "AcDbEntity") (8 . "PLANTS") (62 . 94) (370 . 13) (100 . "AcDbPolyline") (90 . 3) (70 . 0)
(43 . 0.0) (10 18812.2171945701 4057.3148190045) (10 18817.0447963801 4038.6096153846) (10 18831.0690045249
4030.9204751131))
((0 . "LWPOLYLINE") (100 . "AcDbEntity") (8 . "PLANTS") (62 . 94) (370 . 13) (100 . "AcDbPolyline") (90 . 2) (70 . 0)
(43 . 0.0) (10 18815.9898190045 3612.367760181) (10 18812.2171945701 3623.6806561086))
((0 . "LWPOLYLINE") (100 . "AcDbEntity") (8 . "PLANTS") (62 . 94) (370 . 13) (100 . "AcDbPolyline") (90 . 3) (70 . 0)
(43 . 0.0) (10 18849.9264705882 3653.8461538462) (10 18823.6771493213 3642.3858597285) (10 18812.2171945701
3623.6806561086))
((0 . "LWPOLYLINE") (100 . "AcDbEntity") (8 . "PLANTS") (62 . 94) (370 . 13) (100 . "AcDbPolyline") (90 . 2) (70 . 0)
(43 . 0.0) (10 18812.2171945701 3548.2657239819) (10 18834.8416289593 3544.4944570136))
((0 . "LWPOLYLINE") (100 . "AcDbEntity") (8 . "PLANTS") (62 . 94) (370 . 13) (100 . "AcDbPolyline") (90 . 2) (70 . 0)
(43 . 0.0) (10 18812.2171945701 3548.2657239819) (10 18815.9898190045 3612.367760181))
((0 . "LWPOLYLINE") (100 . "AcDbEntity") (8 . "PLANTS") (62 . 94) (370 . 13) (100 . "AcDbPolyline") (90 . 2) (70 . 0)
(43 . 0.0) (10 18812.2171945701 3408.7478506787) (10 18815.9898190045 3386.1234162896))
((0 . "LWPOLYLINE") (100 . "AcDbEntity") (8 . "PLANTS") (62 . 94) (370 . 13) (100 . "AcDbPolyline") (90 . 2) (70 . 0)
(43 . 0.0) (10 18815.9889863582 1381.1690548683) (10 18815.9898190045 1300.9049773756))
((0 . "LWPOLYLINE") (100 . "AcDbEntity") (8 . "PLANTS") (62 . 94) (370 . 13) (100 . "AcDbPolyline") (90 . 3) (70 . 0)
(43 . 0.0) (10 18812.2171945701 1240.5740950226) (10 18812.3649321267 1289.592760181) (10 18815.9898190045
1300.9049773756))
((0 . "LWPOLYLINE") (100 . "AcDbEntity") (8 . "PLANTS") (62 . 94) (370 . 13) (100 . "AcDbPolyline") (90 . 2) (70 . 0)
(43 . 0.0) (10 18863.1221719457 1242.4575791855) (10 18812.2171945701 1240.5740950226))
((0 . "LWPOLYLINE") (100 . "AcDbEntity") (8 . "PLANTS") (62 . 94) (370 . 13) (100 . "AcDbPolyline") (90 . 2) (70 . 0)
(43 . 0.0) (10 18815.9898190045 3925.3393665158) (10 18814.100678733 3940.4227375566))
((0 . "LWPOLYLINE") (100 . "AcDbEntity") (8 . "PLANTS") (62 . 94) (370 . 13) (100 . "AcDbPolyline") (90 . 3) (70 . 0)
(43 . 0.0) (10 18814.100678733 3940.4227375566) (10 18812.3691176471 3951.7349547511) (10 18819.7567873303
3993.2126696833))
((0 . "LWPOLYLINE") (100 . "AcDbEntity") (8 . "PLANTS") (62 . 94) (370 . 13) (100 . "AcDbPolyline") (90 . 2) (70 . 0)
(43 . 0.0) (10 18814.100678733 3940.4227375566) (10 18872.5509049774 3944.1926470588))
((0 . "LWPOLYLINE") (100 . "AcDbEntity") (8 . "PLANTS") (62 . 94) (370 . 13) (100 . "AcDbPolyline") (90 . 3) (70 . 0)
(43 . 0.0) (10 18846.1538461538 3891.4027149321) (10 18823.3885746606 3921.4142533937) (10 18815.9898190045
3925.3393665158))
((0 . "LWPOLYLINE") (100 . "AcDbEntity") (8 . "PLANTS") (62 . 94) (370 . 13) (100 . "AcDbPolyline") (90 . 2) (70 . 0)
(43 . 0.0) (10 18849.9264705882 3612.367760181) (10 18815.9898190045 3612.367760181))
((0 . "LWPOLYLINE") (100 . "AcDbEntity") (8 . "PLANTS") (62 . 94) (370 . 13) (100 . "AcDbPolyline") (90 . 2) (70 . 0)
(43 . 0.0) (10 18815.9898190045 3386.1234162896) (10 18861.2386877828 3382.3529411765))
((0 . "LWPOLYLINE") (100 . "AcDbEntity") (8 . "PLANTS") (62 . 94) (370 . 13) (100 . "AcDbPolyline") (90 . 2) (70 . 0)
(43 . 0.0) (10 18857.4660633484 1304.6747737557) (10 18815.9898190045 1300.9049773756))
((0 . "LWPOLYLINE") (100 . "AcDbEntity") (8 . "PLANTS") (62 . 94) (370 . 13) (100 . "AcDbPolyline") (90 . 2) (70 . 0)
(43 . 0.0) (10 18834.8416289593 3996.9838235294) (10 18819.7567873303 3993.2126696833))
((0 . "LWPOLYLINE") (100 . "AcDbEntity") (8 . "PLANTS") (62 . 94) (370 . 13) (100 . "AcDbPolyline") (90 . 3) (70 . 0)
(43 . 0.0) (10 18846.1538461538 678.7330316742) (10 18831.0690045249 679.7893665158) (10 18819.7567873303
686.2754524887))
((0 . "LWPOLYLINE") (100 . "AcDbEntity") (8 . "PLANTS") (62 . 94) (370 . 13) (100 . "AcDbPolyline") (90 . 2) (70 . 0)
(43 . 0.0) (10 18827.3020361991 3865.0071266968) (10 18846.1538461538 3891.4027149321))
((0 . "LWPOLYLINE") (100 . "AcDbEntity") (8 . "PLANTS") (62 . 94) (370 . 13) (100 . "AcDbPolyline") (90 . 2) (70 . 0)
(43 . 0.0) (10 18834.8416289593 3996.9838235294) (10 18831.0690045249 4030.9204751131))
((0 . "LWPOLYLINE") (100 . "AcDbEntity") (8 . "PLANTS") (62 . 94) (370 . 13) (100 . "AcDbPolyline") (90 . 2) (70 . 0)
(43 . 0.0) (10 18831.0690045249 4030.9204751131) (10 18842.3812217195 4034.6903846154))
((0 . "LWPOLYLINE") (100 . "AcDbEntity") (8 . "PLANTS") (62 . 94) (370 . 13) (100 . "AcDbPolyline") (90 . 2) (70 . 0)
(43 . 0.0) (10 18834.8416289593 3996.9838235294) (10 18853.693438914 3996.9838235294))
((0 . "LWPOLYLINE") (100 . "AcDbEntity") (8 . "PLANTS") (62 . 94) (370 . 13) (100 . "AcDbPolyline") (90 . 2) (70 . 0)
(43 . 0.0) (10 18849.9264705882 3544.4944570136) (10 18834.8416289593 3544.4944570136))
((0 . "LWPOLYLINE") (100 . "AcDbEntity") (8 . "PLANTS") (62 . 94) (370 . 13) (100 . "AcDbPolyline") (90 . 3) (70 . 0)
(43 . 0.0) (10 18834.8416289593 3299.3969457014) (10 18846.1538461538 3299.3969457014) (10 18849.9264705882
3295.625678733))
((0 . "LWPOLYLINE") (100 . "AcDbEntity") (8 . "PLANTS") (62 . 94) (370 . 13) (100 . "AcDbPolyline") (90 . 2) (70 . 0)
(43 . 0.0) (10 18838.6142533937 1134.9915158371) (10 18838.6142533937 1108.5972850679))
((0 . "LWPOLYLINE") (100 . "AcDbEntity") (8 . "PLANTS") (62 . 94) (370 . 13) (100 . "AcDbPolyline") (90 . 3) (70 . 0)
(43 . 0.0) (10 18838.6142533937 1134.9915158371) (10 18856.4097285068 1157.6159502262) (10 18865.0056561086
1176.4705882353))
((0 . "LWPOLYLINE") (100 . "AcDbEntity") (8 . "PLANTS") (62 . 94) (370 . 13) (100 . "AcDbPolyline") (90 . 3) (70 . 0)
(43 . 0.0) (10 18838.6142533937 1108.5972850679) (10 18849.9264705882 1104.9745475113) (10 18891.4027149321
1104.8274886878))
((0 . "LWPOLYLINE") (100 . "AcDbEntity") (8 . "PLANTS") (62 . 94) (370 . 13) (100 . "AcDbPolyline") (90 . 3) (70 . 0)
(43 . 0.0) (10 18838.6142533937 629.7143665158) (10 18856.2618778281 633.6463800905) (10 18857.4660633484
678.7330316742))
((0 . "LWPOLYLINE") (100 . "AcDbEntity") (8 . "PLANTS") (62 . 94) (370 . 13) (100 . "AcDbPolyline") (90 . 2) (70 . 0)
(43 . 0.0) (10 18842.3812217195 4049.7737556561) (10 18842.3812217195 4034.6903846154))
((0 . "LWPOLYLINE") (100 . "AcDbEntity") (8 . "PLANTS") (62 . 94) (370 . 13) (100 . "AcDbPolyline") (90 . 2) (70 . 0)
(43 . 0.0) (10 18842.3812217195 4049.7737556561) (10 18849.9264705882 4068.6270361991))
((0 . "LWPOLYLINE") (100 . "AcDbEntity") (8 . "PLANTS") (62 . 94) (370 . 13) (100 . "AcDbPolyline") (90 . 2) (70 . 0)
(43 . 0.0) (10 18865.0056561086 4023.3781674208) (10 18842.3812217195 4034.6903846154))
((0 . "LWPOLYLINE") (100 . "AcDbEntity") (8 . "PLANTS") (62 . 94) (370 . 13) (100 . "AcDbPolyline") (90 . 3) (70 . 0)
(43 . 0.0) (10 18842.3812217195 878.5831447964) (10 18849.7772624434 844.6464932127) (10 18849.9264705882
818.2494343891))
((0 . "LWPOLYLINE") (100 . "AcDbEntity") (8 . "PLANTS") (62 . 94) (370 . 13) (100 . "AcDbPolyline") (90 . 3) (70 . 0)
(43 . 0.0) (10 18842.3812217195 878.5831447964) (10 18851.1153846154 897.2816742081) (10 18857.4660633484
901.2075791855))
((0 . "LWPOLYLINE") (100 . "AcDbEntity") (8 . "PLANTS") (62 . 94) (370 . 13) (100 . "AcDbPolyline") (90 . 2) (70 . 0)
(43 . 0.0) (10 18898.9423076923 3898.9437782805) (10 18846.1538461538 3891.4027149321))
((0 . "LWPOLYLINE") (100 . "AcDbEntity") (8 . "PLANTS") (62 . 94) (370 . 13) (100 . "AcDbPolyline") (90 . 2) (70 . 0)
(43 . 0.0) (10 18846.1538461538 678.7330316742) (10 18857.4660633484 678.7330316742))
((0 . "LWPOLYLINE") (100 . "AcDbEntity") (8 . "PLANTS") (62 . 94) (370 . 13) (100 . "AcDbPolyline") (90 . 3) (70 . 0)
(43 . 0.0) (10 18846.1538461538 678.7330316742) (10 18853.5470588235 701.3574660633) (10 18853.693438914
765.4609728507))
((0 . "LWPOLYLINE") (100 . "AcDbEntity") (8 . "PLANTS") (62 . 94) (370 . 13) (100 . "AcDbPolyline") (90 . 2) (70 . 0)
(43 . 0.0) (10 18872.5509049774 4068.6270361991) (10 18849.9264705882 4068.6270361991))
((0 . "LWPOLYLINE") (100 . "AcDbEntity") (8 . "PLANTS") (62 . 94) (370 . 13) (100 . "AcDbPolyline") (90 . 2) (70 . 0)
(43 . 0.0) (10 18849.9264705882 3612.367760181) (10 18849.9264705882 3653.8461538462))
((0 . "LWPOLYLINE") (100 . "AcDbEntity") (8 . "PLANTS") (62 . 94) (370 . 13) (100 . "AcDbPolyline") (90 . 2) (70 . 0)
(43 . 0.0) (10 18857.4660633484 3657.6173076923) (10 18849.9264705882 3653.8461538462))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18849.9264705882 3612.367760181 0.0) (10 18855.0343705926 3590.4995568178 0.0) (10 18859.0743219607
3565.8233438367 0.0) (10 18849.9264705882 3544.4944570136 0.0))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.4472811015) (40
. 1) (40 . 1) (40 . 1) (40 . 1) (10 18849.9264705881 3472.8506787331 0.0) (10 18855.2021415901 3484.6269010797 0.0) (10
18886.5879466561 3500.003711417 0.0) (10 18865.0087065436 3537.8987888889 0.0) (10 18849.9264705882 3544.4944570136
0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18849.9264705882 3472.850678733 0.0) (10 18843.2249823638 3440.001812307 0.0) (10 18885.7911251522
3418.8120688607 0.0) (10 18861.2386877828 3382.3529411765 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18849.9264705882 3193.8157239819 0.0) (10 18821.6946729305 3231.4001905823 0.0) (10 18870.0217764494
3260.1483700287 0.0) (10 18849.9264705882 3295.625678733 0.0))
((0 . "LWPOLYLINE") (100 . "AcDbEntity") (8 . "PLANTS") (62 . 94) (370 . 13) (100 . "AcDbPolyline") (90 . 2) (70 . 0)
(43 . 0.0) (10 18857.4660633484 3299.3969457014) (10 18849.9264705882 3295.625678733))
((0 . "LWPOLYLINE") (100 . "AcDbEntity") (8 . "PLANTS") (62 . 94) (370 . 13) (100 . "AcDbPolyline") (90 . 2) (70 . 0)
(43 . 0.0) (10 18853.693438914 810.709841629) (10 18849.9264705882 818.2494343891))
((0 . "LWPOLYLINE") (100 . "AcDbEntity") (8 . "PLANTS") (62 . 94) (370 . 13) (100 . "AcDbPolyline") (90 . 2) (70 . 0)
(43 . 0.0) (10 18857.4660633484 3989.4415158371) (10 18853.693438914 3996.9838235294))
((0 . "LWPOLYLINE") (100 . "AcDbEntity") (8 . "PLANTS") (62 . 94) (370 . 13) (100 . "AcDbPolyline") (90 . 2) (70 . 0)
(43 . 0.0) (10 18865.0056561086 4023.3781674208) (10 18853.693438914 3996.9838235294))
((0 . "LWPOLYLINE") (100 . "AcDbEntity") (8 . "PLANTS") (62 . 94) (370 . 13) (100 . "AcDbPolyline") (90 . 2) (70 . 0)
(43 . 0.0) (10 18853.693438914 810.709841629) (10 18853.693438914 765.4609728507))
((0 . "LWPOLYLINE") (100 . "AcDbEntity") (8 . "PLANTS") (62 . 94) (370 . 13) (100 . "AcDbPolyline") (90 . 3) (70 . 0)
(43 . 0.0) (10 18853.693438914 810.709841629) (10 18865.0056561086 814.3319004525) (10 18902.7149321267 814.479638009))
((0 . "LWPOLYLINE") (100 . "AcDbEntity") (8 . "PLANTS") (62 . 94) (370 . 13) (100 . "AcDbPolyline") (90 . 3) (70 . 0)
(43 . 0.0) (10 18914.0271493213 769.2307692308) (10 18906.4791855204 765.6080316742) (10 18853.693438914
765.4609728507))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18857.4660633484 3699.0950226244 0.0) (10 18880.0089297598 3712.6760737152 0.0) (10 18909.0643668707
3696.305155374 0.0) (10 18910.2545248869 3672.6994343891 0.0))
((0 . "LWPOLYLINE") (100 . "AcDbEntity") (8 . "PLANTS") (62 . 94) (370 . 13) (100 . "AcDbPolyline") (90 . 2) (70 . 0)
(43 . 0.0) (10 18857.4660633484 3657.6173076923) (10 18857.4660633484 3699.0950226244))
((0 . "LWPOLYLINE") (100 . "AcDbEntity") (8 . "PLANTS") (62 . 94) (370 . 13) (100 . "AcDbPolyline") (90 . 2) (70 . 0)
(43 . 0.0) (10 18857.4660633484 3699.0950226244) (10 18861.2386877828 3755.6561085973))
((0 . "LWPOLYLINE") (100 . "AcDbEntity") (8 . "PLANTS") (62 . 94) (370 . 13) (100 . "AcDbPolyline") (90 . 2) (70 . 0)
(43 . 0.0) (10 18857.4660633484 3657.6173076923) (10 18883.8631221719 3657.6173076923))
((0 . "LWPOLYLINE") (100 . "AcDbEntity") (8 . "PLANTS") (62 . 94) (370 . 13) (100 . "AcDbPolyline") (90 . 3) (70 . 0)
(43 . 0.0) (10 18857.4660633484 3299.3969457014) (10 18854.893438914 3352.1867647059) (10 18861.2386877828
3382.3529411765))
((0 . "LWPOLYLINE") (100 . "AcDbEntity") (8 . "PLANTS") (62 . 94) (370 . 13) (100 . "AcDbPolyline") (90 . 2) (70 . 0)
(43 . 0.0) (10 18857.4660633484 3299.3969457014) (10 18886.4152322523 3300.2741318366))
((0 . "LWPOLYLINE") (100 . "AcDbEntity") (8 . "PLANTS") (62 . 94) (370 . 13) (100 . "AcDbPolyline") (90 . 2) (70 . 0)
(43 . 0.0) (10 18925.1915613749 3301.4490898602) (10 18981.9004524887 3303.1674208145))
((0 . "LWPOLYLINE") (100 . "AcDbEntity") (8 . "PLANTS") (62 . 94) (370 . 13) (100 . "AcDbPolyline") (90 . 3) (70 . 0)
(43 . 0.0) (10 18863.1221719457 1242.4575791855) (10 18864.8592760181 1259.4259049774) (10 18857.4660633484
1304.6747737557))
((0 . "LWPOLYLINE") (100 . "AcDbEntity") (8 . "PLANTS") (62 . 94) (370 . 13) (100 . "AcDbPolyline") (90 . 3) (70 . 0)
(43 . 0.0) (10 18857.4660633484 1304.6747737557) (10 18861.2303167421 1319.7596153846) (10 18861.2308133292
1381.2737198261))
((0 . "LWPOLYLINE") (100 . "AcDbEntity") (8 . "PLANTS") (62 . 94) (370 . 13) (100 . "AcDbPolyline") (90 . 3) (70 . 0)
(43 . 0.0) (10 18865.0056561086 1176.4705882353) (10 18858.6618778281 1184.0178733032) (10 18857.4660633484
1199.0950226244))
((0 . "LWPOLYLINE") (100 . "AcDbEntity") (8 . "PLANTS") (62 . 94) (370 . 13) (100 . "AcDbPolyline") (90 . 3) (70 . 0)
(43 . 0.0) (10 18861.2386877828 1206.6374434389) (10 18857.4660633484 1206.6374434389) (10 18857.4660633484
1199.0950226244))
((0 . "LWPOLYLINE") (100 . "AcDbEntity") (8 . "PLANTS") (62 . 94) (370 . 13) (100 . "AcDbPolyline") (90 . 2) (70 . 0)
(43 . 0.0) (10 18861.2386877828 1206.6374434389) (10 18857.4660633484 1199.0950226244))
((0 . "LWPOLYLINE") (100 . "AcDbEntity") (8 . "PLANTS") (62 . 94) (370 . 13) (100 . "AcDbPolyline") (90 . 2) (70 . 0)
(43 . 0.0) (10 18857.4660633484 950.2262443439) (10 18857.4660633484 901.2075791855))
((0 . "LWPOLYLINE") (100 . "AcDbEntity") (8 . "PLANTS") (62 . 94) (370 . 13) (100 . "AcDbPolyline") (90 . 3) (70 . 0)
(43 . 0.0) (10 18883.8631221719 961.5384615385) (10 18865.0140271493 956.5700226244) (10 18857.4660633484
950.2262443439))
((0 . "LWPOLYLINE") (100 . "AcDbEntity") (8 . "PLANTS") (62 . 94) (370 . 13) (100 . "AcDbPolyline") (90 . 3) (70 . 0)
(43 . 0.0) (10 18857.4660633484 901.2075791855) (10 18865.0140271493 894.8631221719) (10 18895.1753393665
889.895361991))
((0 . "LWPOLYLINE") (100 . "AcDbEntity") (8 . "PLANTS") (62 . 94) (370 . 13) (100 . "AcDbPolyline") (90 . 3) (70 . 0)
(43 . 0.0) (10 18917.7997737557 690.0452488688) (10 18898.9423076923 678.8814479638) (10 18857.4660633484
678.7330316742))
((0 . "LWPOLYLINE") (100 . "AcDbEntity") (8 . "PLANTS") (62 . 94) (370 . 13) (100 . "AcDbPolyline") (90 . 2) (70 . 0)
(43 . 0.0) (10 18906.4856334842 4166.667081448) (10 18861.2386877828 4166.667081448))
((0 . "LWPOLYLINE") (100 . "AcDbEntity") (8 . "PLANTS") (62 . 94) (370 . 13) (100 . "AcDbPolyline") (90 . 2) (70 . 0)
(43 . 0.0) (10 18861.2386877828 4144.0426470588) (10 18861.2386877828 4166.667081448))
((0 . "LWPOLYLINE") (100 . "AcDbEntity") (8 . "PLANTS") (62 . 94) (370 . 13) (100 . "AcDbPolyline") (90 . 2) (70 . 0)
(43 . 0.0) (10 18861.2388636102 4209.3214776153) (10 18861.2386877828 4166.667081448))
((0 . "LWPOLYLINE") (100 . "AcDbEntity") (8 . "PLANTS") (62 . 94) (370 . 13) (100 . "AcDbPolyline") (90 . 3) (70 . 0)
(43 . 0.0) (10 18872.5509049774 4068.6270361991) (10 18872.4016968326 4113.8759049774) (10 18861.2386877828
4144.0426470588))
((0 . "LWPOLYLINE") (100 . "AcDbEntity") (8 . "PLANTS") (62 . 94) (370 . 13) (100 . "AcDbPolyline") (90 . 3) (70 . 0)
(43 . 0.0) (10 18891.4027149321 3763.1971719457) (10 18876.3178733032 3756.7058823529) (10 18861.2386877828
3755.6561085973))
((0 . "LWPOLYLINE") (100 . "AcDbEntity") (8 . "PLANTS") (62 . 94) (370 . 13) (100 . "AcDbPolyline") (90 . 2) (70 . 0)
(43 . 0.0) (10 18863.1221719457 1242.4575791855) (10 18861.2386877828 1206.6374434389))
((0 . "LWPOLYLINE") (100 . "AcDbEntity") (8 . "PLANTS") (62 . 94) (370 . 13) (100 . "AcDbPolyline") (90 . 2) (70 . 0)
(43 . 0.0) (10 18861.2386877828 1206.6374434389) (10 18887.6300904977 1210.407239819))
((0 . "LWPOLYLINE") (100 . "AcDbEntity") (8 . "PLANTS") (62 . 94) (370 . 13) (100 . "AcDbPolyline") (90 . 2) (70 . 0)
(43 . 0.0) (10 18863.1221719457 1242.4575791855) (10 18883.8631221719 1244.3438914027))
((0 . "LWPOLYLINE") (100 . "AcDbEntity") (8 . "PLANTS") (62 . 94) (370 . 13) (100 . "AcDbPolyline") (90 . 2) (70 . 0)
(43 . 0.0) (10 18895.1753393665 4023.3781674208) (10 18865.0056561086 4023.3781674208))
((0 . "LWPOLYLINE") (100 . "AcDbEntity") (8 . "PLANTS") (62 . 94) (370 . 13) (100 . "AcDbPolyline") (90 . 2) (70 . 0)
(43 . 0.0) (10 18891.4027149321 1180.2403846154) (10 18865.0056561086 1176.4705882353))
((0 . "LWPOLYLINE") (100 . "AcDbEntity") (8 . "PLANTS") (62 . 94) (370 . 13) (100 . "AcDbPolyline") (90 . 2) (70 . 0)
(43 . 0.0) (10 18872.5509049774 4068.6270361991) (10 18883.8631221719 4064.8571266968))
((0 . "LWPOLYLINE") (100 . "AcDbEntity") (8 . "PLANTS") (62 . 94) (370 . 13) (100 . "AcDbPolyline") (90 . 2) (70 . 0)
(43 . 0.0) (10 18902.7149321267 3914.0271493213) (10 18872.5509049774 3944.1926470588))
((0 . "LWPOLYLINE") (100 . "AcDbEntity") (8 . "PLANTS") (62 . 94) (370 . 13) (100 . "AcDbPolyline") (90 . 3) (70 . 0)
(43 . 0.0) (10 18895.1753393665 3963.0471719457) (10 18880.09739819 3959.1213800905) (10 18872.5509049774
3944.1926470588))
((0 . "LWPOLYLINE") (100 . "AcDbEntity") (8 . "PLANTS") (62 . 94) (370 . 13) (100 . "AcDbPolyline") (90 . 3) (70 . 0)
(43 . 0.0) (10 18895.1753393665 4023.3781674208) (10 18887.7792986425 4038.4615384615) (10 18883.8631221719
4064.8571266968))
((0 . "LWPOLYLINE") (100 . "AcDbEntity") (8 . "PLANTS") (62 . 94) (370 . 13) (100 . "AcDbPolyline") (90 . 2) (70 . 0)
(43 . 0.0) (10 18883.8631221719 4064.8571266968) (10 18898.9423076923 4072.3981900452))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6418542291) (40
. 1) (40 . 1) (40 . 1) (40 . 1) (10 18940.4242081449 3604.8268099548 0.0) (10 18917.8038142166 3598.9171920958 0.0) (10
18892.1741272088 3616.662132935 0.0) (10 18888.0757867913 3648.5318500015 0.0) (10 18883.863122172 3657.6173076923 0.0))
((0 . "LWPOLYLINE") (100 . "AcDbEntity") (8 . "PLANTS") (62 . 94) (370 . 13) (100 . "AcDbPolyline") (90 . 3) (70 . 0)
(43 . 0.0) (10 18910.2545248869 3672.6994343891) (10 18895.1753393665 3667.7247737557) (10 18883.8631221719
3657.6173076923))
((0 . "LWPOLYLINE") (100 . "AcDbEntity") (8 . "PLANTS") (62 . 94) (370 . 13) (100 . "AcDbPolyline") (90 . 2) (70 . 0)
(43 . 0.0) (10 18883.8631221719 1244.3438914027) (10 18883.8631221719 1233.0316742081))
((0 . "LWPOLYLINE") (100 . "AcDbEntity") (8 . "PLANTS") (62 . 94) (370 . 13) (100 . "AcDbPolyline") (90 . 3) (70 . 0)
(43 . 0.0) (10 18883.8631221719 1244.3438914027) (10 18895.1734162896 1263.1985294118) (10 18895.1734162896
1297.1351809955))
((0 . "LWPOLYLINE") (100 . "AcDbEntity") (8 . "PLANTS") (62 . 94) (370 . 13) (100 . "AcDbPolyline") (90 . 2) (70 . 0)
(43 . 0.0) (10 18919.6832579186 1233.0316742081) (10 18883.8631221719 1233.0316742081))
((0 . "LWPOLYLINE") (100 . "AcDbEntity") (8 . "PLANTS") (62 . 94) (370 . 13) (100 . "AcDbPolyline") (90 . 2) (70 . 0)
(43 . 0.0) (10 18883.8631221719 1225.4892533937) (10 18883.8631221719 1233.0316742081))
((0 . "LWPOLYLINE") (100 . "AcDbEntity") (8 . "PLANTS") (62 . 94) (370 . 13) (100 . "AcDbPolyline") (90 . 3) (70 . 0)
(43 . 0.0) (10 18883.8631221719 1225.4892533937) (10 18876.3178733032 1229.2618778281) (10 18883.8631221719
1233.0316742081))
((0 . "LWPOLYLINE") (100 . "AcDbEntity") (8 . "PLANTS") (62 . 94) (370 . 13) (100 . "AcDbPolyline") (90 . 3) (70 . 0)
(43 . 0.0) (10 18883.8631221719 1225.4892533937) (10 18887.6300904977 1221.7194570136) (10 18887.6300904977
1210.407239819))
((0 . "LWPOLYLINE") (100 . "AcDbEntity") (8 . "PLANTS") (62 . 94) (370 . 13) (100 . "AcDbPolyline") (90 . 2) (70 . 0)
(43 . 0.0) (10 18902.7149321267 953.996040724) (10 18883.8631221719 961.5384615385))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18883.8631221719 961.5384615385 0.0) (10 18909.7457477421 1005.1800547305 0.0) (10 18901.2954633968
1058.0800985615 0.0) (10 18891.4027149321 1104.8274886878 0.0))
((0 . "LWPOLYLINE") (100 . "AcDbEntity") (8 . "PLANTS") (62 . 94) (370 . 13) (100 . "AcDbPolyline") (90 . 3) (70 . 0)
(43 . 0.0) (10 18891.4027149321 1180.2403846154) (10 18891.2549773756 1202.8599547511) (10 18887.6300904977
1210.407239819))
((0 . "LWPOLYLINE") (100 . "AcDbEntity") (8 . "PLANTS") (62 . 94) (370 . 13) (100 . "AcDbPolyline") (90 . 3) (70 . 0)
(43 . 0.0) (10 18891.4027149321 3763.1971719457) (10 18910.2545248869 3745.5484162896) (10 18932.878959276
3740.5727375566))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18891.4027149321 3763.1971719457 0.0) (10 18913.1031997988 3797.9318072764 0.0) (10 18935.3753488551
3867.3960434358 0.0) (10 18898.9423076924 3898.9437782806 0.0))
((0 . "LWPOLYLINE") (100 . "AcDbEntity") (8 . "PLANTS") (62 . 94) (370 . 13) (100 . "AcDbPolyline") (90 . 2) (70 . 0)
(43 . 0.0) (10 18921.5667420814 1180.2403846154) (10 18891.4027149321 1180.2403846154))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18891.4027149321 1104.8274886878 0.0) (10 18908.7567124773 1135.0862987684 0.0) (10 18947.8920600017
1105.7007926439 0.0) (10 18974.3608597285 1119.9095022624 0.0))
((0 . "LWPOLYLINE") (100 . "AcDbEntity") (8 . "PLANTS") (62 . 94) (370 . 13) (100 . "AcDbPolyline") (90 . 2) (70 . 0)
(43 . 0.0) (10 18923.4558823529 1297.1351809955) (10 18895.1734162896 1297.1351809955))
((0 . "LWPOLYLINE") (100 . "AcDbEntity") (8 . "PLANTS") (62 . 94) (370 . 13) (100 . "AcDbPolyline") (90 . 2) (70 . 0)
(43 . 0.0) (10 18895.1734162896 1353.6953549208) (10 18895.1734162896 1297.1351809955))
((0 . "LWPOLYLINE") (100 . "AcDbEntity") (8 . "PLANTS") (62 . 94) (370 . 13) (100 . "AcDbPolyline") (90 . 2) (70 . 0)
(43 . 0.0) (10 18895.1753393665 4023.3781674208) (10 18906.4875565611 4023.3781674208))
((0 . "LWPOLYLINE") (100 . "AcDbEntity") (8 . "PLANTS") (62 . 94) (370 . 13) (100 . "AcDbPolyline") (90 . 3) (70 . 0)
(43 . 0.0) (10 18895.1753393665 3963.0471719457) (10 18896.2303167421 3940.4227375566) (10 18910.2545248869
3921.5682126697))
((0 . "LWPOLYLINE") (100 . "AcDbEntity") (8 . "PLANTS") (62 . 94) (370 . 13) (100 . "AcDbPolyline") (90 . 2) (70 . 0)
(43 . 0.0) (10 18895.1753393665 3963.0471719457) (10 18906.4875565611 4000.7537330317))
((0 . "LWPOLYLINE") (100 . "AcDbEntity") (8 . "PLANTS") (62 . 94) (370 . 13) (100 . "AcDbPolyline") (90 . 2) (70 . 0)
(43 . 0.0) (10 18895.1753393665 859.7285067873) (10 18895.1753393665 889.895361991))
((0 . "LWPOLYLINE") (100 . "AcDbEntity") (8 . "PLANTS") (62 . 94) (370 . 13) (100 . "AcDbPolyline") (90 . 2) (70 . 0)
(43 . 0.0) (10 18930.9954751131 899.3212669683) (10 18895.1753393665 889.895361991))
((0 . "LWPOLYLINE") (100 . "AcDbEntity") (8 . "PLANTS") (62 . 94) (370 . 13) (100 . "AcDbPolyline") (90 . 3) (70 . 0)
(43 . 0.0) (10 18898.9423076923 4072.3981900452) (10 18914.0271493213 4058.3714932127) (10 18925.3393665158
4053.5449095023))
((0 . "LWPOLYLINE") (100 . "AcDbEntity") (8 . "PLANTS") (62 . 94) (370 . 13) (100 . "AcDbPolyline") (90 . 2) (70 . 0)
(43 . 0.0) (10 18910.2545248869 4095.0226244344) (10 18898.9423076923 4072.3981900452))
((0 . "LWPOLYLINE") (100 . "AcDbEntity") (8 . "PLANTS") (62 . 94) (370 . 13) (100 . "AcDbPolyline") (90 . 3) (70 . 0)
(43 . 0.0) (10 18898.9423076923 3898.9437782805) (10 18898.9423076923 3910.2559954751) (10 18902.7149321267
3914.0271493213))
((0 . "LWPOLYLINE") (100 . "AcDbEntity") (8 . "PLANTS") (62 . 94) (370 . 13) (100 . "AcDbPolyline") (90 . 3) (70 . 0)
(43 . 0.0) (10 18900.0546481579 522.0889475987) (10 18903.9191176471 554.2924208145) (10 18910.4628073599
560.1437796813))
((0 . "LWPOLYLINE") (100 . "AcDbEntity") (8 . "PLANTS") (62 . 94) (370 . 13) (100 . "AcDbPolyline") (90 . 2) (70 . 0)
(43 . 0.0) (10 18922.2229894927 603.1419456043) (10 18917.7997737557 610.8597285068))
((0 . "LWPOLYLINE") (100 . "AcDbEntity") (8 . "PLANTS") (62 . 94) (370 . 13) (100 . "AcDbPolyline") (90 . 2) (70 . 0)
(43 . 0.0) (10 18910.2545248869 3921.5682126697) (10 18902.7149321267 3914.0271493213))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18930.9954751131 899.3212669683 0.0) (10 18911.7462298105 912.3245196665 0.0) (10 18924.4307180722
942.0169749382 0.0) (10 18902.7149321267 953.996040724 0.0))
((0 . "LWPOLYLINE") (100 . "AcDbEntity") (8 . "PLANTS") (62 . 94) (370 . 13) (100 . "AcDbPolyline") (90 . 3) (70 . 0)
(43 . 0.0) (10 18951.7364253394 969.0808823529) (10 18921.5667420814 964.2595022624) (10 18902.7149321267
953.996040724))
((0 . "LWPOLYLINE") (100 . "AcDbEntity") (8 . "PLANTS") (62 . 94) (370 . 13) (100 . "AcDbPolyline") (90 . 2) (70 . 0)
(43 . 0.0) (10 18902.7149321267 814.479638009) (10 18914.0271493213 769.2307692308))
((0 . "LWPOLYLINE") (100 . "AcDbEntity") (8 . "PLANTS") (62 . 94) (370 . 13) (100 . "AcDbPolyline") (90 . 2) (70 . 0)
(43 . 0.0) (10 18902.7149321267 814.479638009) (10 18932.878959276 833.3342760181))
((0 . "LWPOLYLINE") (100 . "AcDbEntity") (8 . "PLANTS") (62 . 94) (370 . 13) (100 . "AcDbPolyline") (90 . 2) (70 . 0)
(43 . 0.0) (10 18906.4856334842 4172.5584770928) (10 18906.4856334842 4166.667081448))
((0 . "LWPOLYLINE") (100 . "AcDbEntity") (8 . "PLANTS") (62 . 94) (370 . 13) (100 . "AcDbPolyline") (90 . 2) (70 . 0)
(43 . 0.0) (10 18921.5667420814 4159.1247737557) (10 18906.4856334842 4166.667081448))
((0 . "LWPOLYLINE") (100 . "AcDbEntity") (8 . "PLANTS") (62 . 94) (370 . 13) (100 . "AcDbPolyline") (90 . 2) (70 . 0)
(43 . 0.0) (10 18906.4875565611 4023.3781674208) (10 18906.4875565611 4000.7537330317))
((0 . "LWPOLYLINE") (100 . "AcDbEntity") (8 . "PLANTS") (62 . 94) (370 . 13) (100 . "AcDbPolyline") (90 . 2) (70 . 0)
(43 . 0.0) (10 18925.3393665158 4038.4615384615) (10 18906.4875565611 4023.3781674208))
((0 . "LWPOLYLINE") (100 . "AcDbEntity") (8 . "PLANTS") (62 . 94) (370 . 13) (100 . "AcDbPolyline") (90 . 2) (70 . 0)
(43 . 0.0) (10 18951.7364253394 4004.5248868778) (10 18906.4875565611 4000.7537330317))
((0 . "LWPOLYLINE") (100 . "AcDbEntity") (8 . "PLANTS") (62 . 94) (370 . 13) (100 . "AcDbPolyline") (90 . 2) (70 . 0)
(43 . 0.0) (10 18910.2545248869 4095.0226244344) (10 18932.878959276 4087.481561086))
((0 . "LWPOLYLINE") (100 . "AcDbEntity") (8 . "PLANTS") (62 . 94) (370 . 13) (100 . "AcDbPolyline") (90 . 3) (70 . 0)
(43 . 0.0) (10 18921.5667420814 4159.1247737557) (10 18910.4037330317 4117.6470588235) (10 18910.2545248869
4095.0226244344))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18955.5033936652 3932.8804298643 0.0) (10 18938.5100251514 3935.8921470057 0.0) (10 18927.7351108228
3916.4266880723 0.0) (10 18910.2545248869 3921.5682126697 0.0))
((0 . "LWPOLYLINE") (100 . "AcDbEntity") (8 . "PLANTS") (62 . 94) (370 . 13) (100 . "AcDbPolyline") (90 . 3) (70 . 0)
(43 . 0.0) (10 18944.1911764706 3667.0433257919) (10 18936.6446832579 3665.3806561086) (10 18910.2545248869
3672.6994343891))
((0 . "LWPOLYLINE") (100 . "AcDbEntity") (8 . "PLANTS") (62 . 94) (370 . 13) (100 . "AcDbPolyline") (90 . 2) (70 . 0)
(43 . 0.0) (10 18910.2545248869 607.0899321267) (10 18917.7997737557 610.8597285068))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6217649285) (40
. 1) (40 . 1) (40 . 1) (40 . 1) (10 18917.7997737557 690.0452488688 0.0) (10 18908.5649616817 706.1726364686 0.0) (10
18909.9087192833 737.5154684655 0.0) (10 18925.743626589 763.2804164393 0.0) (10 18914.0271493214 769.2307692308 0.0))
((0 . "LWPOLYLINE") (100 . "AcDbEntity") (8 . "PLANTS") (62 . 94) (370 . 13) (100 . "AcDbPolyline") (90 . 2) (70 . 0)
(43 . 0.0) (10 18917.7997737557 690.0452488688) (10 18938.186248141 690.0452488688))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18930.2025597825 632.3172494763 0.0) (10 18921.2378901682 632.8332796513 0.0) (10 18919.6879548114
613.2604878655 0.0) (10 18917.7997737557 610.8597285068 0.0))
((0 . "LWPOLYLINE") (100 . "AcDbEntity") (8 . "PLANTS") (62 . 94) (370 . 13) (100 . "AcDbPolyline") (90 . 2) (70 . 0)
(43 . 0.0) (10 18919.6832579186 1233.0316742081) (10 18951.7364253394 1233.0316742081))
((0 . "LWPOLYLINE") (100 . "AcDbEntity") (8 . "PLANTS") (62 . 94) (370 . 13) (100 . "AcDbPolyline") (90 . 2) (70 . 0)
(43 . 0.0) (10 18919.6832579186 1233.0316742081) (10 18921.5667420814 1180.2403846154))
((0 . "LWPOLYLINE") (100 . "AcDbEntity") (8 . "PLANTS") (62 . 94) (370 . 13) (100 . "AcDbPolyline") (90 . 3) (70 . 0)
(43 . 0.0) (10 18919.6832579186 1233.0316742081) (10 18925.1916289593 1270.7381221719) (10 18923.4558823529
1297.1351809955))
((0 . "LWPOLYLINE") (100 . "AcDbEntity") (8 . "PLANTS") (62 . 94) (370 . 13) (100 . "AcDbPolyline") (90 . 2) (70 . 0)
(43 . 0.0) (10 18921.5667420814 1180.2403846154) (10 18929.1119909502 1180.2403846154))
((0 . "LWPOLYLINE") (100 . "AcDbEntity") (8 . "PLANTS") (62 . 94) (370 . 13) (100 . "AcDbPolyline") (90 . 2) (70 . 0)
(43 . 0.0) (10 18923.4558823529 1297.1351809955) (10 18955.5033936652 1297.1351809955))
((0 . "LWPOLYLINE") (100 . "AcDbEntity") (8 . "PLANTS") (62 . 94) (370 . 13) (100 . "AcDbPolyline") (90 . 2) (70 . 0)
(43 . 0.0) (10 18923.4558823529 1297.1351809955) (10 18923.3037576678 1330.839452551))
((0 . "LWPOLYLINE") (100 . "AcDbEntity") (8 . "PLANTS") (62 . 94) (370 . 13) (100 . "AcDbPolyline") (90 . 2) (70 . 0)
(43 . 0.0) (10 18925.3393665158 4038.4615384615) (10 18925.3393665158 4053.5449095023))
((0 . "LWPOLYLINE") (100 . "AcDbEntity") (8 . "PLANTS") (62 . 94) (370 . 13) (100 . "AcDbPolyline") (90 . 2) (70 . 0)
(43 . 0.0) (10 18932.878959276 4087.481561086) (10 18925.3393665158 4053.5449095023))
((0 . "LWPOLYLINE") (100 . "AcDbEntity") (8 . "PLANTS") (62 . 94) (370 . 13) (100 . "AcDbPolyline") (90 . 2) (70 . 0)
(43 . 0.0) (10 18951.7364253394 4030.9204751131) (10 18925.3393665158 4038.4615384615))
((0 . "LWPOLYLINE") (100 . "AcDbEntity") (8 . "PLANTS") (62 . 94) (370 . 13) (100 . "AcDbPolyline") (90 . 3) (70 . 0)
(43 . 0.0) (10 18970.5882352941 1153.8461538462) (10 18940.5705882353 1158.8208144796) (10 18929.1119909502
1180.2403846154))
((0 . "LWPOLYLINE") (100 . "AcDbEntity") (8 . "PLANTS") (62 . 94) (370 . 13) (100 . "AcDbPolyline") (90 . 3) (70 . 0)
(43 . 0.0) (10 18955.5033936652 1195.3252262443) (10 18940.4242081448 1190.3554298643) (10 18929.1119909502
1180.2403846154))
((0 . "LWPOLYLINE") (100 . "AcDbEntity") (8 . "PLANTS") (62 . 94) (370 . 13) (100 . "AcDbPolyline") (90 . 3) (70 . 0)
(43 . 0.0) (10 18930.9954751131 899.3212669683) (10 18936.6446832579 878.5831447964) (10 18932.878959276
833.3342760181))
((0 . "LWPOLYLINE") (100 . "AcDbEntity") (8 . "PLANTS") (62 . 94) (370 . 13) (100 . "AcDbPolyline") (90 . 3) (70 . 0)
(43 . 0.0) (10 18957.4193058118 904.914565035) (10 18944.1898190045 904.8261312217) (10 18930.9954751131
899.3212669683))
((0 . "LWPOLYLINE") (100 . "AcDbEntity") (8 . "PLANTS") (62 . 94) (370 . 13) (100 . "AcDbPolyline") (90 . 2) (70 . 0)
(43 . 0.0) (10 18959.2760180996 4087.481561086) (10 18932.878959276 4087.481561086))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18944.1911764706 3680.2417420814 0.0) (10 18926.8935159107 3694.3646442588 0.0) (10 18935.5807591321
3722.4934546897 0.0) (10 18932.878959276 3740.5727375566 0.0))
((0 . "LWPOLYLINE") (100 . "AcDbEntity") (8 . "PLANTS") (62 . 94) (370 . 13) (100 . "AcDbPolyline") (90 . 3) (70 . 0)
(43 . 0.0) (10 18963.0486425339 3785.8216063348) (10 18952.7914027149 3778.274321267) (10 18932.878959276
3740.5727375566))
((0 . "LWPOLYLINE") (100 . "AcDbEntity") (8 . "PLANTS") (62 . 94) (370 . 13) (100 . "AcDbPolyline") (90 . 2) (70 . 0)
(43 . 0.0) (10 18932.878959276 833.3342760181) (10 18950.6152236755 828.9002099182))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18936.6515837104 3536.9535067873 0.0) (10 18920.3846966312 3560.7488280776 0.0) (10 18975.2121854427
3559.8294578571 0.0) (10 18955.5033936652 3589.7433257919 0.0))
((0 . "LWPOLYLINE") (100 . "AcDbEntity") (8 . "PLANTS") (62 . 94) (370 . 13) (100 . "AcDbPolyline") (90 . 2) (70 . 0)
(43 . 0.0) (10 18955.5033936652 3589.7433257919) (10 18940.4242081448 3604.8268099548))
((0 . "LWPOLYLINE") (100 . "AcDbEntity") (8 . "PLANTS") (62 . 94) (370 . 13) (100 . "AcDbPolyline") (90 . 2) (70 . 0)
(43 . 0.0) (10 18944.1911764706 3667.0433257919) (10 18940.4242081448 3604.8268099548))
((0 . "LWPOLYLINE") (100 . "AcDbEntity") (8 . "PLANTS") (62 . 94) (370 . 13) (100 . "AcDbPolyline") (90 . 2) (70 . 0)
(43 . 0.0) (10 18944.1911764706 3667.0433257919) (10 18944.1911764706 3680.2417420814))
((0 . "LWPOLYLINE") (100 . "AcDbEntity") (8 . "PLANTS") (62 . 94) (370 . 13) (100 . "AcDbPolyline") (90 . 3) (70 . 0)
(43 . 0.0) (10 18944.1911764706 3680.2417420814) (10 18978.1278280543 3712.9736425339) (10 18996.9852941176
3714.1783936652))
((0 . "LWPOLYLINE") (100 . "AcDbEntity") (8 . "PLANTS") (62 . 94) (370 . 13) (100 . "AcDbPolyline") (90 . 2) (70 . 0)
(43 . 0.0) (10 18944.1911764706 3667.0433257919) (10 18970.5882352941 3668.9295248869))
((0 . "LWPOLYLINE") (100 . "AcDbEntity") (8 . "PLANTS") (62 . 94) (370 . 13) (100 . "AcDbPolyline") (90 . 2) (70 . 0)
(43 . 0.0) (10 18951.7364253394 4030.9204751131) (10 18951.7364253394 4004.5248868778))
((0 . "LWPOLYLINE") (100 . "AcDbEntity") (8 . "PLANTS") (62 . 94) (370 . 13) (100 . "AcDbPolyline") (90 . 2) (70 . 0)
(43 . 0.0) (10 18951.7364253394 4030.9204751131) (10 18963.0486425339 4034.6903846154))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18951.7364253394 4004.5248868778 0.0) (10 18965.2283867317 3990.2312333664 0.0) (10 18986.6637845424
4003.8757170992 0.0) (10 19000.7522624434 3989.4415158371 0.0))
((0 . "LWPOLYLINE") (100 . "AcDbEntity") (8 . "PLANTS") (62 . 94) (370 . 13) (100 . "AcDbPolyline") (90 . 3) (70 . 0)
(43 . 0.0) (10 18963.0486425339 3435.1435520362) (10 18959.2760180996 3431.3722850679) (10 18951.7364253394
3435.1435520362))
((0 . "LWPOLYLINE") (100 . "AcDbEntity") (8 . "PLANTS") (62 . 94) (370 . 13) (100 . "AcDbPolyline") (90 . 2) (70 . 0)
(43 . 0.0) (10 18951.7364253394 1233.0316742081) (10 18959.2760180996 1214.1770361991))
((0 . "LWPOLYLINE") (100 . "AcDbEntity") (8 . "PLANTS") (62 . 94) (370 . 13) (100 . "AcDbPolyline") (90 . 3) (70 . 0)
(43 . 0.0) (10 18951.7364253394 1233.0316742081) (10 18959.4237556561 1244.1961538462) (10 18974.3608597285
1251.8863122172))
((0 . "LWPOLYLINE") (100 . "AcDbEntity") (8 . "PLANTS") (62 . 94) (370 . 13) (100 . "AcDbPolyline") (90 . 3) (70 . 0)
(43 . 0.0) (10 18951.7364253394 969.0808823529) (10 18966.8156108597 968.0237556561) (10 18978.1278280543
957.7686651584))
((0 . "LWPOLYLINE") (100 . "AcDbEntity") (8 . "PLANTS") (62 . 94) (370 . 13) (100 . "AcDbPolyline") (90 . 3) (70 . 0)
(43 . 0.0) (10 18951.7364253394 969.0808823529) (10 18956.7033936652 999.2449095023) (10 18970.5882352941
1010.5571266968))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18955.5033936651 3932.8804298642 0.0) (10 18970.4376017788 3907.7996819817 0.0) (10 19007.3361933776
3906.5883409606 0.0) (10 19034.6889140271 3906.4860859728 0.0))
((0 . "LWPOLYLINE") (100 . "AcDbEntity") (8 . "PLANTS") (62 . 94) (370 . 13) (100 . "AcDbPolyline") (90 . 3) (70 . 0)
(43 . 0.0) (10 18993.2126696833 3955.5048642534) (10 18966.8156108597 3942.995361991) (10 18955.5033936652
3932.8804298643))
((0 . "LWPOLYLINE") (100 . "AcDbEntity") (8 . "PLANTS") (62 . 94) (370 . 13) (100 . "AcDbPolyline") (90 . 3) (70 . 0)
(43 . 0.0) (10 18955.5033936652 3589.7433257919) (10 18985.6730769231 3602.1119909502) (10 19000.7522624434
3616.1390271493))
((0 . "LWPOLYLINE") (100 . "AcDbEntity") (8 . "PLANTS") (62 . 94) (370 . 13) (100 . "AcDbPolyline") (90 . 3) (70 . 0)
(43 . 0.0) (10 19021.4932126697 3440.7996606335) (10 18970.5951357466 3401.2) (10 18955.5033936652 3374.811199095))
((0 . "LWPOLYLINE") (100 . "AcDbEntity") (8 . "PLANTS") (62 . 94) (370 . 13) (100 . "AcDbPolyline") (90 . 3) (70 . 0)
(43 . 0.0) (10 18955.5033936652 1297.1351809955) (10 18964.2444570136 1270.7457013575) (10 18974.3608597285
1263.1985294118))
((0 . "LWPOLYLINE") (100 . "AcDbEntity") (8 . "PLANTS") (62 . 94) (370 . 13) (100 . "AcDbPolyline") (90 . 2) (70 . 0)
(43 . 0.0) (10 18955.5033936652 1297.1351809955) (10 18959.6652229655 1301.2957619967))
((0 . "LWPOLYLINE") (100 . "AcDbEntity") (8 . "PLANTS") (62 . 94) (370 . 13) (100 . "AcDbPolyline") (90 . 2) (70 . 0)
(43 . 0.0) (10 18955.5033936652 1195.3252262443) (10 18974.3608597285 1172.7007918552))
((0 . "LWPOLYLINE") (100 . "AcDbEntity") (8 . "PLANTS") (62 . 94) (370 . 13) (100 . "AcDbPolyline") (90 . 2) (70 . 0)
(43 . 0.0) (10 18955.5033936652 1195.3252262443) (10 18959.2760180996 1214.1770361991))
((0 . "LWPOLYLINE") (100 . "AcDbEntity") (8 . "PLANTS") (62 . 94) (370 . 13) (100 . "AcDbPolyline") (90 . 2) (70 . 0)
(43 . 0.0) (10 18966.8156108597 4072.3981900452) (10 18959.2760180996 4087.481561086))
((0 . "LWPOLYLINE") (100 . "AcDbEntity") (8 . "PLANTS") (62 . 94) (370 . 13) (100 . "AcDbPolyline") (90 . 3) (70 . 0)
(43 . 0.0) (10 18974.3608597285 4110.1059954751) (10 18960.4802036199 4098.7937782805) (10 18959.2760180996
4087.481561086))
((0 . "LWPOLYLINE") (100 . "AcDbEntity") (8 . "PLANTS") (62 . 94) (370 . 13) (100 . "AcDbPolyline") (90 . 2) (70 . 0)
(43 . 0.0) (10 18963.0486425339 3785.8216063348) (10 18959.2760180996 3804.6761312217))
((0 . "LWPOLYLINE") (100 . "AcDbEntity") (8 . "PLANTS") (62 . 94) (370 . 13) (100 . "AcDbPolyline") (90 . 2) (70 . 0)
(43 . 0.0) (10 18981.9004524887 3751.8849547511) (10 18959.2760180996 3740.5727375566))
((0 . "LWPOLYLINE") (100 . "AcDbEntity") (8 . "PLANTS") (62 . 94) (370 . 13) (100 . "AcDbPolyline") (90 . 2) (70 . 0)
(43 . 0.0) (10 18985.6730769231 1214.1770361991) (10 18959.2760180996 1214.1770361991))
((0 . "LWPOLYLINE") (100 . "AcDbEntity") (8 . "PLANTS") (62 . 94) (370 . 13) (100 . "AcDbPolyline") (90 . 3) (70 . 0)
(43 . 0.0) (10 18959.2760180996 1070.8908371041) (10 18973.1608597285 1052.036199095) (10 18974.3608597285
1036.9541855204))
((0 . "LWPOLYLINE") (100 . "AcDbEntity") (8 . "PLANTS") (62 . 94) (370 . 13) (100 . "AcDbPolyline") (90 . 2) (70 . 0)
(43 . 0.0) (10 18966.8156108597 4072.3981900452) (10 18963.0486425339 4034.6903846154))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18987.556561086 4072.3981900452 0.0) (10 19002.0982824523 4054.8467207372 0.0) (10 18984.7253780312
4024.75133085 0.0) (10 18963.0486425339 4034.6903846154 0.0))
((0 . "LWPOLYLINE") (100 . "AcDbEntity") (8 . "PLANTS") (62 . 94) (370 . 13) (100 . "AcDbPolyline") (90 . 3) (70 . 0)
(43 . 0.0) (10 18981.9004524887 3751.8849547511) (10 18973.3030542986 3781.896719457) (10 18963.0486425339
3785.8216063348))
((0 . "LWPOLYLINE") (100 . "AcDbEntity") (8 . "PLANTS") (62 . 94) (370 . 13) (100 . "AcDbPolyline") (90 . 2) (70 . 0)
(43 . 0.0) (10 18966.8156108597 4072.3981900452) (10 18987.556561086 4072.3981900452))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18966.8156108597 3887.631561086 0.0) (10 18991.9394002073 3860.5447119531 0.0) (10 18995.3034938129
3806.8820398037 0.0) (10 19030.9219457014 3785.8216063348 0.0))
((0 . "LWPOLYLINE") (100 . "AcDbEntity") (8 . "PLANTS") (62 . 94) (370 . 13) (100 . "AcDbPolyline") (90 . 2) (70 . 0)
(43 . 0.0) (10 18969.2396141157 916.2895927602) (10 18978.1278280543 957.7686651584))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19027.149321267 3657.6173076923 0.0) (10 19019.7017961056 3664.0249195965 0.0) (10 18977.0044318649
3646.96402384 0.0) (10 18970.5882352941 3668.9295248869 0.0))
((0 . "LWPOLYLINE") (100 . "AcDbEntity") (8 . "PLANTS") (62 . 94) (370 . 13) (100 . "AcDbPolyline") (90 . 3) (70 . 0)
(43 . 0.0) (10 18970.5882352941 3668.9295248869) (10 18988.3850678733 3687.7828054299) (10 18996.9852941176
3714.1783936652))
((0 . "LWPOLYLINE") (100 . "AcDbEntity") (8 . "PLANTS") (62 . 94) (370 . 13) (100 . "AcDbPolyline") (90 . 3) (70 . 0)
(43 . 0.0) (10 18970.5882352941 3208.8992081448) (10 18993.3604072398 3246.6001131222) (10 19030.9219457014
3280.5429864253))
((0 . "LWPOLYLINE") (100 . "AcDbEntity") (8 . "PLANTS") (62 . 94) (370 . 13) (100 . "AcDbPolyline") (90 . 2) (70 . 0)
(43 . 0.0) (10 18970.5882352941 1153.8461538462) (10 18974.3608597285 1127.4519230769))
((0 . "LWPOLYLINE") (100 . "AcDbEntity") (8 . "PLANTS") (62 . 94) (370 . 13) (100 . "AcDbPolyline") (90 . 2) (70 . 0)
(43 . 0.0) (10 18970.5882352941 1153.8461538462) (10 18974.3608597285 1172.7007918552))
((0 . "LWPOLYLINE") (100 . "AcDbEntity") (8 . "PLANTS") (62 . 94) (370 . 13) (100 . "AcDbPolyline") (90 . 2) (70 . 0)
(43 . 0.0) (10 18970.5882352941 1010.5571266968) (10 18996.9852941176 991.7053167421))
((0 . "LWPOLYLINE") (100 . "AcDbEntity") (8 . "PLANTS") (62 . 94) (370 . 13) (100 . "AcDbPolyline") (90 . 2) (70 . 0)
(43 . 0.0) (10 18970.5882352941 1010.5571266968) (10 18974.3608597285 1036.9541855204))
((0 . "LWPOLYLINE") (100 . "AcDbEntity") (8 . "PLANTS") (62 . 94) (370 . 13) (100 . "AcDbPolyline") (90 . 2) (70 . 0)
(43 . 0.0) (10 18974.3608597285 4110.1059954751) (10 18974.3608597285 4117.4098557692))
((0 . "LWPOLYLINE") (100 . "AcDbEntity") (8 . "PLANTS") (62 . 94) (370 . 13) (100 . "AcDbPolyline") (90 . 3) (70 . 0)
(43 . 0.0) (10 18974.3608597285 4110.1059954751) (10 18984.4675339367 4102.5574660633) (10 18987.556561086
4072.3981900452))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.4968512332)
(40 . 0.7230636292) (40 . 1) (40 . 1) (40 . 1) (40 . 1) (10 18974.3608597286 3461.5384615385 0.0) (10 18945.0720142375
3462.469109902 0.0) (10 18943.4416701091 3510.025709257 0.0) (10 18988.2645128667 3527.1089505678 0.0) (10
19006.0294679375 3507.5776206929 0.0) (10 19015.8371040723 3503.0168552035 0.0))
((0 . "LWPOLYLINE") (100 . "AcDbEntity") (8 . "PLANTS") (62 . 94) (370 . 13) (100 . "AcDbPolyline") (90 . 2) (70 . 0)
(43 . 0.0) (10 18989.4400452489 3152.3381221719) (10 18981.3252887152 3136.1044086681))
((0 . "LWPOLYLINE") (100 . "AcDbEntity") (8 . "PLANTS") (62 . 94) (370 . 13) (100 . "AcDbPolyline") (90 . 2) (70 . 0)
(43 . 0.0) (10 18974.3608597285 1251.8863122172) (10 18974.3608597285 1263.1985294118))
((0 . "LWPOLYLINE") (100 . "AcDbEntity") (8 . "PLANTS") (62 . 94) (370 . 13) (100 . "AcDbPolyline") (90 . 2) (70 . 0)
(43 . 0.0) (10 18990.5819704466 1276.1759046682) (10 18974.3608597285 1263.1985294118))
((0 . "LWPOLYLINE") (100 . "AcDbEntity") (8 . "PLANTS") (62 . 94) (370 . 13) (100 . "AcDbPolyline") (90 . 3) (70 . 0)
(43 . 0.0) (10 18974.3608597285 1251.8863122172) (10 18984.4675339367 1240.5740950226) (10 18985.6730769231
1229.2618778281))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18985.6730769231 1214.1770361991 0.0) (10 18991.551255518 1205.9563871974 0.0) (10 18995.8276120885
1170.7632487508 0.0) (10 18974.3608597285 1172.7007918552 0.0))
((0 . "LWPOLYLINE") (100 . "AcDbEntity") (8 . "PLANTS") (62 . 94) (370 . 13) (100 . "AcDbPolyline") (90 . 2) (70 . 0)
(43 . 0.0) (10 18974.3608597285 1127.4519230769) (10 18974.3608597285 1119.9095022624))
((0 . "LWPOLYLINE") (100 . "AcDbEntity") (8 . "PLANTS") (62 . 94) (370 . 13) (100 . "AcDbPolyline") (90 . 3) (70 . 0)
(43 . 0.0) (10 19030.9219457014 1138.7641402715) (10 19008.2975113122 1131.3694570136) (10 18974.3608597285
1127.4519230769))
((0 . "LWPOLYLINE") (100 . "AcDbEntity") (8 . "PLANTS") (62 . 94) (370 . 13) (100 . "AcDbPolyline") (90 . 3) (70 . 0)
(43 . 0.0) (10 19046.0011312217 1067.1182126697) (10 18989.4484162896 1094.5709276018) (10 18974.3608597285
1119.9095022624))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 18996.9852941177 991.7053167421 0.0) (10 19015.8833259199 1006.3272997673 0.0) (10 18995.8882910255
1041.1359728854 0.0) (10 18974.3608597285 1036.9541855204 0.0))
((0 . "LWPOLYLINE") (100 . "AcDbEntity") (8 . "PLANTS") (62 . 94) (370 . 13) (100 . "AcDbPolyline") (90 . 2) (70 . 0)
(43 . 0.0) (10 18978.1278280543 957.7686651584) (10 19000.7522624434 957.7686651584))
((0 . "LWPOLYLINE") (100 . "AcDbEntity") (8 . "PLANTS") (62 . 94) (370 . 13) (100 . "AcDbPolyline") (90 . 3) (70 . 0)
(43 . 0.0) (10 18981.9004524887 3751.8849547511) (10 18992.0168552036 3740.5727375566) (10 18996.9852941176
3714.1783936652))
((0 . "LWPOLYLINE") (100 . "AcDbEntity") (8 . "PLANTS") (62 . 94) (370 . 13) (100 . "AcDbPolyline") (90 . 3) (70 . 0)
(43 . 0.0) (10 19030.9219457014 3299.3969457014) (10 18989.4484162896 3299.5446832579) (10 18981.9004524887
3303.1674208145))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19051.657239819 3350.3019230769 0.0) (10 19018.7483378102 3365.1792232421 0.0) (10 18983.009675469
3336.4446886305 0.0) (10 18981.9004524887 3303.1674208145 0.0))
((0 . "LWPOLYLINE") (100 . "AcDbEntity") (8 . "PLANTS") (62 . 94) (370 . 13) (100 . "AcDbPolyline") (90 . 3) (70 . 0)
(43 . 0.0) (10 19019.6097285068 3073.15260181) (10 19015.6838235294 3065.7523755656) (10 19007.2419000847
3060.5142921737))
((0 . "LWPOLYLINE") (100 . "AcDbEntity") (8 . "PLANTS") (62 . 94) (370 . 13) (100 . "AcDbPolyline") (90 . 2) (70 . 0)
(43 . 0.0) (10 19030.9219457014 3009.0497737557) (10 19024.3212108695 3010.699635718))
((0 . "LWPOLYLINE") (100 . "AcDbEntity") (8 . "PLANTS") (62 . 94) (370 . 13) (100 . "AcDbPolyline") (90 . 2) (70 . 0)
(43 . 0.0) (10 18985.6730769231 1229.2618778281) (10 18985.6730769231 1214.1770361991))
((0 . "LWPOLYLINE") (100 . "AcDbEntity") (8 . "PLANTS") (62 . 94) (370 . 13) (100 . "AcDbPolyline") (90 . 2) (70 . 0)
(43 . 0.0) (10 18985.6730769231 1229.2618778281) (10 19027.149321267 1233.0316742081))
((0 . "LWPOLYLINE") (100 . "AcDbEntity") (8 . "PLANTS") (62 . 94) (370 . 13) (100 . "AcDbPolyline") (90 . 2) (70 . 0)
(43 . 0.0) (10 18987.556561086 4072.3981900452) (10 19030.9219457014 4076.1693438914))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19040.3450226244 3930.9954751131 0.0) (10 19031.5821803876 3952.4662907344 0.0) (10 19004.8567984693
3939.0776065395 0.0) (10 18993.2126696833 3955.5048642534 0.0))
((0 . "LWPOLYLINE") (100 . "AcDbEntity") (8 . "PLANTS") (62 . 94) (370 . 13) (100 . "AcDbPolyline") (90 . 3) (70 . 0)
(43 . 0.0) (10 18993.2126696833 3955.5048642534) (10 18993.3604072398 3970.5882352941) (10 19000.7522624434
3989.4415158371))
((0 . "LWPOLYLINE") (100 . "AcDbEntity") (8 . "PLANTS") (62 . 94) (370 . 13) (100 . "AcDbPolyline") (90 . 2) (70 . 0)
(43 . 0.0) (10 19000.7522624434 957.7686651584) (10 18996.9852941176 991.7053167421))
((0 . "LWPOLYLINE") (100 . "AcDbEntity") (8 . "PLANTS") (62 . 94) (370 . 13) (100 . "AcDbPolyline") (90 . 2) (70 . 0)
(43 . 0.0) (10 19019.6097285068 4004.5248868778) (10 19000.7522624434 3989.4415158371))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19000.7522624434 957.7686651584 0.0) (10 19018.6858166819 953.0194339706 0.0) (10 19031.598256832
934.3502660498 0.0) (10 19030.8025747088 916.2895927602 0.0))
((0 . "LWPOLYLINE") (100 . "AcDbEntity") (8 . "PLANTS") (62 . 94) (370 . 13) (100 . "AcDbPolyline") (90 . 3) (70 . 0)
(43 . 0.0) (10 19008.2975113122 3182.5035067873) (10 19012.2205882353 3193.8095022624) (10 19030.9219457014
3205.1279411765))
((0 . "LWPOLYLINE") (100 . "AcDbEntity") (8 . "PLANTS") (62 . 94) (370 . 13) (100 . "AcDbPolyline") (90 . 3) (70 . 0)
(43 . 0.0) (10 19021.4932126697 3440.7996606335) (10 19012.2136877828 3457.7679864253) (10 19015.8371040724
3503.0168552036))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19027.149321267 3657.6173076923 0.0) (10 19018.7239883959 3611.9069100538 0.0) (10 19049.8397601486
3544.8729978396 0.0) (10 19015.8371040724 3503.0168552036 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19019.6097285068 4004.5248868778 0.0) (10 19071.1707624287 3985.5683226033 0.0) (10 19130.1389180093
4060.2432248141 0.0) (10 19174.2081447964 4019.6082579186 0.0))
((0 . "LWPOLYLINE") (100 . "AcDbEntity") (8 . "PLANTS") (62 . 94) (370 . 13) (100 . "AcDbPolyline") (90 . 3) (70 . 0)
(43 . 0.0) (10 19019.6097285068 4004.5248868778) (10 19030.7727375566 4046.00260181) (10 19030.9219457014
4076.1693438914))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19021.4932126698 3440.7996606335 0.0) (10 19033.5011421225 3416.1326593478 0.0) (10 19024.8923919863
3374.9108847428 0.0) (10 19053.5463800905 3359.7285067873 0.0))
((0 . "LWPOLYLINE") (100 . "AcDbEntity") (8 . "PLANTS") (62 . 94) (370 . 13) (100 . "AcDbPolyline") (90 . 2) (70 . 0)
(43 . 0.0) (10 19021.4932126697 3440.7996606335) (10 19076.1708144796 3465.3089366516))
((0 . "LWPOLYLINE") (100 . "AcDbEntity") (8 . "PLANTS") (62 . 94) (370 . 13) (100 . "AcDbPolyline") (90 . 2) (70 . 0)
(43 . 0.0) (10 19030.8793513202 4088.0081921678) (10 19030.9219457014 4076.1693438914))
((0 . "LWPOLYLINE") (100 . "AcDbEntity") (8 . "PLANTS") (62 . 94) (370 . 13) (100 . "AcDbPolyline") (90 . 3) (70 . 0)
(43 . 0.0) (10 19027.149321267 3657.6173076923) (10 19034.684841629 3699.0950226244) (10 19030.9219457014
3785.8216063348))
((0 . "LWPOLYLINE") (100 . "AcDbEntity") (8 . "PLANTS") (62 . 94) (370 . 13) (100 . "AcDbPolyline") (90 . 2) (70 . 0)
(43 . 0.0) (10 19036.4852988136 2975.2210458813) (10 19046.0011312217 2963.8009049774))
((0 . "LWPOLYLINE") (100 . "AcDbEntity") (8 . "PLANTS") (62 . 94) (370 . 13) (100 . "AcDbPolyline") (90 . 2) (70 . 0)
(43 . 0.0) (10 19030.9219457014 3009.0497737557) (10 19028.9471940088 2997.207184895))
((0 . "LWPOLYLINE") (100 . "AcDbEntity") (8 . "PLANTS") (62 . 94) (370 . 13) (100 . "AcDbPolyline") (90 . 3) (70 . 0)
(43 . 0.0) (10 19030.9219457014 1138.7641402715) (10 19027.2970588235 1150.0763574661) (10 19027.149321267
1233.0316742081))
((0 . "LWPOLYLINE") (100 . "AcDbEntity") (8 . "PLANTS") (62 . 94) (370 . 13) (100 . "AcDbPolyline") (90 . 2) (70 . 0)
(43 . 0.0) (10 19030.9219457014 1240.5740950226) (10 19027.149321267 1233.0316742081))
((0 . "LWPOLYLINE") (100 . "AcDbEntity") (8 . "PLANTS") (62 . 94) (370 . 13) (100 . "AcDbPolyline") (90 . 2) (70 . 0)
(43 . 0.0) (10 19030.9219457014 1240.5740950226) (10 19030.9208468409 1259.9657493883))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.3356548398)
(40 . 0.5331236831) (40 . 0.8343647861) (40 . 1) (40 . 1) (40 . 1) (40 . 1) (10 19049.7737556561 4034.6903846154 0.0)
(10 19067.8715406804 4039.9919605072 0.0) (10 19087.9090464345 4054.4369307649 0.0) (10 19112.2268538749 4114.0819461034
0.0) (10 19047.796493547 4082.5097970105 0.0) (10 19055.2195233107 4072.491373191 0.0) (10 19030.9219457014
4076.1693438914 0.0))
((0 . "LWPOLYLINE") (100 . "AcDbEntity") (8 . "PLANTS") (62 . 94) (370 . 13) (100 . "AcDbPolyline") (90 . 2) (70 . 0)
(43 . 0.0) (10 19030.9219457014 3785.8216063348) (10 19079.9377828054 3783.9366515837))
((0 . "LWPOLYLINE") (100 . "AcDbEntity") (8 . "PLANTS") (62 . 94) (370 . 13) (100 . "AcDbPolyline") (90 . 2) (70 . 0)
(43 . 0.0) (10 19030.9219457014 3299.3969457014) (10 19030.9219457014 3280.5429864253))
((0 . "LWPOLYLINE") (100 . "AcDbEntity") (8 . "PLANTS") (62 . 94) (370 . 13) (100 . "AcDbPolyline") (90 . 3) (70 . 0)
(43 . 0.0) (10 19030.9219457014 3299.3969457014) (10 19039.5178733032 3333.3335972851) (10 19051.657239819
3350.3019230769))
((0 . "LWPOLYLINE") (100 . "AcDbEntity") (8 . "PLANTS") (62 . 94) (370 . 13) (100 . "AcDbPolyline") (90 . 2) (70 . 0)
(43 . 0.0) (10 19038.4615384615 3280.5429864253) (10 19030.9219457014 3280.5429864253))
((0 . "LWPOLYLINE") (100 . "AcDbEntity") (8 . "PLANTS") (62 . 94) (370 . 13) (100 . "AcDbPolyline") (90 . 2) (70 . 0)
(43 . 0.0) (10 19042.2341628959 3197.5869909502) (10 19030.9219457014 3205.1279411765))
((0 . "LWPOLYLINE") (100 . "AcDbEntity") (8 . "PLANTS") (62 . 94) (370 . 13) (100 . "AcDbPolyline") (90 . 3) (70 . 0)
(43 . 0.0) (10 19046.0011312217 3223.9819004525) (10 19035.8875565611 3216.2924208145) (10 19030.9219457014
3205.1279411765))
((0 . "LWPOLYLINE") (100 . "AcDbEntity") (8 . "PLANTS") (62 . 94) (370 . 13) (100 . "AcDbPolyline") (90 . 2) (70 . 0)
(43 . 0.0) (10 19042.2341628959 3197.5869909502) (10 19030.9219457014 3163.6503393665))
((0 . "LWPOLYLINE") (100 . "AcDbEntity") (8 . "PLANTS") (62 . 94) (370 . 13) (100 . "AcDbPolyline") (90 . 2) (70 . 0)
(43 . 0.0) (10 19030.9219457014 3148.5668552036) (10 19046.0011312217 3114.6302036199))
((0 . "LWPOLYLINE") (100 . "AcDbEntity") (8 . "PLANTS") (62 . 94) (370 . 13) (100 . "AcDbPolyline") (90 . 2) (70 . 0)
(43 . 0.0) (10 19030.9219457014 3009.0497737557) (10 19042.2341628959 3012.8202488688))
((0 . "LWPOLYLINE") (100 . "AcDbEntity") (8 . "PLANTS") (62 . 94) (370 . 13) (100 . "AcDbPolyline") (90 . 2) (70 . 0)
(43 . 0.0) (10 19030.9219457014 1240.5740950226) (10 19076.1708144796 1244.3438914027))
((0 . "LWPOLYLINE") (100 . "AcDbEntity") (8 . "PLANTS") (62 . 94) (370 . 13) (100 . "AcDbPolyline") (90 . 2) (70 . 0)
(43 . 0.0) (10 19030.9219457014 1138.7641402715) (10 19057.3133484163 1138.7641402715))
((0 . "LWPOLYLINE") (100 . "AcDbEntity") (8 . "PLANTS") (62 . 94) (370 . 13) (100 . "AcDbPolyline") (90 . 3) (70 . 0)
(43 . 0.0) (10 19034.6889140272 3906.4860859729) (10 19039.6573529412 3887.631561086) (10 19076.1708144796
3842.3826923077))
((0 . "LWPOLYLINE") (100 . "AcDbEntity") (8 . "PLANTS") (62 . 94) (370 . 13) (100 . "AcDbPolyline") (90 . 3) (70 . 0)
(43 . 0.0) (10 19040.3450226244 3930.9954751131) (10 19034.9126696833 3921.6358597285) (10 19034.6889140272
3906.4860859729))
((0 . "LWPOLYLINE") (100 . "AcDbEntity") (8 . "PLANTS") (62 . 94) (370 . 13) (100 . "AcDbPolyline") (90 . 2) (70 . 0)
(43 . 0.0) (10 19038.4615384615 3280.5429864253) (10 19046.0011312217 3223.9819004525))
((0 . "LWPOLYLINE") (100 . "AcDbEntity") (8 . "PLANTS") (62 . 94) (370 . 13) (100 . "AcDbPolyline") (90 . 2) (70 . 0)
(43 . 0.0) (10 19038.4615384615 3280.5429864253) (10 19064.8585972851 3284.3134615385))
((0 . "LWPOLYLINE") (100 . "AcDbEntity") (8 . "PLANTS") (62 . 94) (370 . 13) (100 . "AcDbPolyline") (90 . 3) (70 . 0)
(43 . 0.0) (10 19040.3450226244 3930.9954751131) (10 19068.6255656109 3911.3126696833) (10 19121.4196832579
3910.2559954751))
((0 . "LWPOLYLINE") (100 . "AcDbEntity") (8 . "PLANTS") (62 . 94) (370 . 13) (100 . "AcDbPolyline") (90 . 2) (70 . 0)
(43 . 0.0) (10 19040.3450226244 3930.9954751131) (10 19049.7737556561 3944.1926470588))
((0 . "LWPOLYLINE") (100 . "AcDbEntity") (8 . "PLANTS") (62 . 94) (370 . 13) (100 . "AcDbPolyline") (90 . 2) (70 . 0)
(43 . 0.0) (10 19064.8585972851 3207.0135746606) (10 19042.2341628959 3197.5869909502))
((0 . "LWPOLYLINE") (100 . "AcDbEntity") (8 . "PLANTS") (62 . 94) (370 . 13) (100 . "AcDbPolyline") (90 . 2) (70 . 0)
(43 . 0.0) (10 19042.2341628959 3012.8202488688) (10 19064.8585972851 3009.0497737557))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19042.2341628959 3012.8202488688 0.0) (10 19025.7771605968 3043.4358792519 0.0) (10 19066.2798305413
3055.1481491556 0.0) (10 19053.5463800905 3084.4648190045 0.0))
((0 . "LWPOLYLINE") (100 . "AcDbEntity") (8 . "PLANTS") (62 . 94) (370 . 13) (100 . "AcDbPolyline") (90 . 3) (70 . 0)
(43 . 0.0) (10 19064.8585972851 3207.0135746606) (10 19057.1669683258 3219.1515837104) (10 19046.0011312217
3223.9819004525))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19053.5463800905 3084.4648190045 0.0) (10 19069.3265949041 3093.9462515037 0.0) (10 19057.964737103
3111.5447936179 0.0) (10 19046.0011312217 3114.6302036199 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19053.5463800905 3084.4648190045 0.0) (10 19038.3107628818 3082.9057458497 0.0) (10 19030.0641372677
3110.6647287142 0.0) (10 19046.0011312217 3114.6302036199 0.0))
((0 . "LWPOLYLINE") (100 . "AcDbEntity") (8 . "PLANTS") (62 . 94) (370 . 13) (100 . "AcDbPolyline") (90 . 2) (70 . 0)
(43 . 0.0) (10 19043.6968523297 2954.187348126) (10 19046.0011312217 2963.8009049774))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19064.8585972851 3009.0497737557 0.0) (10 19067.5414077052 2996.7666812407 0.0) (10 19067.703822348
2963.4994133084 0.0) (10 19046.0011312217 2963.8009049774 0.0))
((0 . "LWPOLYLINE") (100 . "AcDbEntity") (8 . "PLANTS") (62 . 94) (370 . 13) (100 . "AcDbPolyline") (90 . 2) (70 . 0)
(43 . 0.0) (10 19049.7737556561 1048.2664027149) (10 19046.0011312217 1067.1182126697))
((0 . "LWPOLYLINE") (100 . "AcDbEntity") (8 . "PLANTS") (62 . 94) (370 . 13) (100 . "AcDbPolyline") (90 . 2) (70 . 0)
(43 . 0.0) (10 19072.3981900452 1070.8908371041) (10 19046.0011312217 1067.1182126697))
((0 . "LWPOLYLINE") (100 . "AcDbEntity") (8 . "PLANTS") (62 . 94) (370 . 13) (100 . "AcDbPolyline") (90 . 3) (70 . 0)
(43 . 0.0) (10 19049.7737556561 3944.1926470588) (10 19057.4639140272 3963.0471719457) (10 19079.9377828054
3981.9004524887))
((0 . "LWPOLYLINE") (100 . "AcDbEntity") (8 . "PLANTS") (62 . 94) (370 . 13) (100 . "AcDbPolyline") (90 . 3) (70 . 0)
(43 . 0.0) (10 19127.0757918552 3942.3076923077) (10 19110.1074660633 3947.9575791855) (10 19049.7737556561
3944.1926470588))
((0 . "LWPOLYLINE") (100 . "AcDbEntity") (8 . "PLANTS") (62 . 94) (370 . 13) (100 . "AcDbPolyline") (90 . 3) (70 . 0)
(43 . 0.0) (10 19108.2183257919 1014.3297511312) (10 19079.9461538462 1022.9264705882) (10 19049.7737556561
1048.2664027149))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19049.773755656 1048.266402715 0.0) (10 19028.1377283023 1012.9387288577 0.0) (10 19095.6901262885
993.129472584 0.0) (10 19079.9377828054 953.996040724 0.0))
((0 . "LWPOLYLINE") (100 . "AcDbEntity") (8 . "PLANTS") (62 . 94) (370 . 13) (100 . "AcDbPolyline") (90 . 2) (70 . 0)
(43 . 0.0) (10 19051.657239819 3350.3019230769) (10 19068.6255656109 3337.1040723982))
((0 . "LWPOLYLINE") (100 . "AcDbEntity") (8 . "PLANTS") (62 . 94) (370 . 13) (100 . "AcDbPolyline") (90 . 2) (70 . 0)
(43 . 0.0) (10 19051.657239819 3350.3019230769) (10 19053.5463800905 3359.7285067873))
((0 . "LWPOLYLINE") (100 . "AcDbEntity") (8 . "PLANTS") (62 . 94) (370 . 13) (100 . "AcDbPolyline") (90 . 3) (70 . 0)
(43 . 0.0) (10 19087.4830316742 3397.4356334842) (10 19076.0202488688 3374.9597285068) (10 19053.5463800905
3359.7285067873))
((0 . "LWPOLYLINE") (100 . "AcDbEntity") (8 . "PLANTS") (62 . 94) (370 . 13) (100 . "AcDbPolyline") (90 . 2) (70 . 0)
(43 . 0.0) (10 19064.8585972851 3207.0135746606) (10 19061.0859728507 3193.8157239819))
((0 . "LWPOLYLINE") (100 . "AcDbEntity") (8 . "PLANTS") (62 . 94) (370 . 13) (100 . "AcDbPolyline") (90 . 2) (70 . 0)
(43 . 0.0) (10 19115.0678974129 2816.7463199135) (10 19090.8191041518 2816.7474469781))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19079.9377828054 3208.8992081448 0.0) (10 19094.0562573054 3234.4053757716 0.0) (10 19084.8201416835
3265.5298961522 0.0) (10 19064.8585972851 3284.3134615385 0.0))
((0 . "LWPOLYLINE") (100 . "AcDbEntity") (8 . "PLANTS") (62 . 94) (370 . 13) (100 . "AcDbPolyline") (90 . 3) (70 . 0)
(43 . 0.0) (10 19064.8585972851 3284.3134615385) (10 19072.2504524887 3306.9378959276) (10 19068.6255656109
3337.1040723982))
((0 . "LWPOLYLINE") (100 . "AcDbEntity") (8 . "PLANTS") (62 . 94) (370 . 13) (100 . "AcDbPolyline") (90 . 2) (70 . 0)
(43 . 0.0) (10 19064.8585972851 3207.0135746606) (10 19079.9377828054 3208.8992081448))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19064.8585972851 3156.1085972851 0.0) (10 19057.7163898338 3192.6160016309 0.0) (10 19122.9543577561
3138.211396978 0.0) (10 19110.1074660633 3129.7136877828 0.0))
((0 . "LWPOLYLINE") (100 . "AcDbEntity") (8 . "PLANTS") (62 . 94) (370 . 13) (100 . "AcDbPolyline") (90 . 2) (70 . 0)
(43 . 0.0) (10 19064.8585972851 3009.0497737557) (10 19106.334841629 3012.8202488688))
((0 . "LWPOLYLINE") (100 . "AcDbEntity") (8 . "PLANTS") (62 . 94) (370 . 13) (100 . "AcDbPolyline") (90 . 2) (70 . 0)
(43 . 0.0) (10 19110.1074660633 3340.8745475113) (10 19068.6255656109 3337.1040723982))
((0 . "LWPOLYLINE") (100 . "AcDbEntity") (8 . "PLANTS") (62 . 94) (370 . 13) (100 . "AcDbPolyline") (90 . 3) (70 . 0)
(43 . 0.0) (10 19072.3981900452 1070.8908371041) (10 19095.0226244344 1056.8631221719) (10 19106.334841629
1055.8059954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19130.842760181 1059.5786199095 0.0) (10 19139.3132592882 1095.8329211691 0.0) (10 19071.4327188462
1109.9100157603 0.0) (10 19072.3981900452 1070.8908371041 0.0))
((0 . "LWPOLYLINE") (100 . "AcDbEntity") (8 . "PLANTS") (62 . 94) (370 . 13) (100 . "AcDbPolyline") (90 . 2) (70 . 0)
(43 . 0.0) (10 19132.7319004525 3842.3826923077) (10 19076.1708144796 3842.3826923077))
((0 . "LWPOLYLINE") (100 . "AcDbEntity") (8 . "PLANTS") (62 . 94) (370 . 13) (100 . "AcDbPolyline") (90 . 2) (70 . 0)
(43 . 0.0) (10 19076.1708144796 3842.3826923077) (10 19079.9377828054 3783.9366515837))
((0 . "LWPOLYLINE") (100 . "AcDbEntity") (8 . "PLANTS") (62 . 94) (370 . 13) (100 . "AcDbPolyline") (90 . 2) (70 . 0)
(43 . 0.0) (10 19083.7104072398 3465.3089366516) (10 19076.1708144796 3465.3089366516))
((0 . "LWPOLYLINE") (100 . "AcDbEntity") (8 . "PLANTS") (62 . 94) (370 . 13) (100 . "AcDbPolyline") (90 . 3) (70 . 0)
(43 . 0.0) (10 19076.1708144796 3465.3089366516) (10 19073.5940045249 3480.3924208145) (10 19087.4830316742
3589.7433257919))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19132.7319004525 3729.260520362 0.0) (10 19106.6845933979 3744.5413367106 0.0) (10 19127.8257537485
3789.930793856 0.0) (10 19079.9377828054 3783.9366515837 0.0))
((0 . "LWPOLYLINE") (100 . "AcDbEntity") (8 . "PLANTS") (62 . 94) (370 . 13) (100 . "AcDbPolyline") (90 . 2) (70 . 0)
(43 . 0.0) (10 19087.4830316742 3589.7433257919) (10 19079.9377828054 3783.9366515837))
((0 . "LWPOLYLINE") (100 . "AcDbEntity") (8 . "PLANTS") (62 . 94) (370 . 13) (100 . "AcDbPolyline") (90 . 3) (70 . 0)
(43 . 0.0) (10 19079.9377828054 3208.8992081448) (10 19091.1036199095 3203.9300904977) (10 19098.7952488688
3193.8157239819))
((0 . "LWPOLYLINE") (100 . "AcDbEntity") (8 . "PLANTS") (62 . 94) (370 . 13) (100 . "AcDbPolyline") (90 . 2) (70 . 0)
(43 . 0.0) (10 19102.5622171946 2914.781561086) (10 19079.9377828054 2937.4059954751))
((0 . "LWPOLYLINE") (100 . "AcDbEntity") (8 . "PLANTS") (62 . 94) (370 . 13) (100 . "AcDbPolyline") (90 . 2) (70 . 0)
(43 . 0.0) (10 19144.0441176471 942.6838235294) (10 19162.5935520362 916.2895927602))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19122.1811448001 916.2895927602 0.0) (10 19113.1287444064 933.2150282462 0.0) (10 19097.0207322937
945.8656917771 0.0) (10 19079.9377828054 953.996040724 0.0))
((0 . "LWPOLYLINE") (100 . "AcDbEntity") (8 . "PLANTS") (62 . 94) (370 . 13) (100 . "AcDbPolyline") (90 . 3) (70 . 0)
(43 . 0.0) (10 19084.1631625822 916.2895927602) (10 19077.2257918552 931.3716063348) (10 19079.9377828054
953.996040724))
((0 . "LWPOLYLINE") (100 . "AcDbEntity") (8 . "PLANTS") (62 . 94) (370 . 13) (100 . "AcDbPolyline") (90 . 3) (70 . 0)
(43 . 0.0) (10 19083.7104072398 3465.3089366516) (10 19087.3338235294 3453.996719457) (10 19087.4830316742
3397.4356334842))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.6424921053) (40
. 1) (40 . 1) (40 . 1) (40 . 1) (10 19083.7104072398 3465.3089366516 0.0) (10 19109.7052446177 3459.8678631675 0.0) (10
19123.1964559047 3506.4335343855 0.0) (10 19154.0660056214 3506.5421519673 0.0) (10 19166.6685520363 3495.4751131221
0.0))
((0 . "LWPOLYLINE") (100 . "AcDbEntity") (8 . "PLANTS") (62 . 94) (370 . 13) (100 . "AcDbPolyline") (90 . 3) (70 . 0)
(43 . 0.0) (10 19106.334841629 3012.8202488688) (10 19105.1390271493 3042.9864253394) (10 19083.7104072398
3073.15260181))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19087.4830316742 3589.7433257919 0.0) (10 19127.2345465092 3587.7179907507 0.0) (10 19101.9726652841
3545.4554769672 0.0) (10 19121.4196832579 3525.6412895928 0.0))
((0 . "LWPOLYLINE") (100 . "AcDbEntity") (8 . "PLANTS") (62 . 94) (370 . 13) (100 . "AcDbPolyline") (90 . 2) (70 . 0)
(43 . 0.0) (10 19087.4830316742 3397.4356334842) (10 19132.7319004525 3412.5191176471))
((0 . "LWPOLYLINE") (100 . "AcDbEntity") (8 . "PLANTS") (62 . 94) (370 . 13) (100 . "AcDbPolyline") (90 . 2) (70 . 0)
(43 . 0.0) (10 19106.334841629 3012.8202488688) (10 19113.8744343891 3009.0497737557))
((0 . "LWPOLYLINE") (100 . "AcDbEntity") (8 . "PLANTS") (62 . 94) (370 . 13) (100 . "AcDbPolyline") (90 . 2) (70 . 0)
(43 . 0.0) (10 19108.2183257919 1014.3297511312) (10 19106.334841629 1055.8059954751))
((0 . "LWPOLYLINE") (100 . "AcDbEntity") (8 . "PLANTS") (62 . 94) (370 . 13) (100 . "AcDbPolyline") (90 . 2) (70 . 0)
(43 . 0.0) (10 19130.842760181 1059.5786199095) (10 19106.334841629 1055.8059954751))
((0 . "LWPOLYLINE") (100 . "AcDbEntity") (8 . "PLANTS") (62 . 94) (370 . 13) (100 . "AcDbPolyline") (90 . 2) (70 . 0)
(43 . 0.0) (10 19108.2183257919 1014.3297511312) (10 19117.6470588235 1014.3297511312))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19108.2183257919 1014.3297511312 0.0) (10 19099.2140066937 991.8409538305 0.0) (10 19126.461484756
970.8235410806 0.0) (10 19132.7319004525 953.996040724 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.5298416604)
(40 . 0.7155085662) (40 . 1) (40 . 1) (40 . 1) (40 . 1) (10 19110.1074660634 3340.8745475113 0.0) (10 19137.119840689
3339.7055043153 0.0) (10 19158.0947902864 3307.6220393697 0.0) (10 19214.514072289 3290.9434442696 0.0) (10
19207.4324466061 3324.585759995 0.0) (10 19193.0599547511 3333.3335972851 0.0))
((0 . "LWPOLYLINE") (100 . "AcDbEntity") (8 . "PLANTS") (62 . 94) (370 . 13) (100 . "AcDbPolyline") (90 . 3) (70 . 0)
(43 . 0.0) (10 19110.1074660633 3340.8745475113) (10 19110.2538461538 3322.0213800905) (10 19117.6470588235
3299.3969457014))
((0 . "LWPOLYLINE") (100 . "AcDbEntity") (8 . "PLANTS") (62 . 94) (370 . 13) (100 . "AcDbPolyline") (90 . 2) (70 . 0)
(43 . 0.0) (10 19113.8744343891 3009.0497737557) (10 19117.6470588235 2982.6548642534))
((0 . "LWPOLYLINE") (100 . "AcDbEntity") (8 . "PLANTS") (62 . 94) (370 . 13) (100 . "AcDbPolyline") (90 . 2) (70 . 0)
(43 . 0.0) (10 19152.1792750636 3009.0507313767) (10 19113.8744343891 3009.0497737557))
((0 . "LWPOLYLINE") (100 . "AcDbEntity") (8 . "PLANTS") (62 . 94) (370 . 13) (100 . "AcDbPolyline") (90 . 2) (70 . 0)
(43 . 0.0) (10 19140.2714932127 3857.4660633484) (10 19121.4196832579 3910.2559954751))
((0 . "LWPOLYLINE") (100 . "AcDbEntity") (8 . "PLANTS") (62 . 94) (370 . 13) (100 . "AcDbPolyline") (90 . 3) (70 . 0)
(43 . 0.0) (10 19127.0757918552 3942.3076923077) (10 19121.6392533937 3932.9480769231) (10 19121.4196832579
3910.2559954751))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19127.0757918552 3942.3076923077 0.0) (10 19149.6724549926 3931.1851269094 0.0) (10 19180.1042121788
3925.2091057032 0.0) (10 19200.6052036199 3944.1926470588 0.0))
((0 . "LWPOLYLINE") (100 . "AcDbEntity") (8 . "PLANTS") (62 . 94) (370 . 13) (100 . "AcDbPolyline") (90 . 3) (70 . 0)
(43 . 0.0) (10 19127.0757918552 3942.3076923077) (10 19133.9277149321 3962.8921945701) (10 19140.2714932127
3966.817081448))
((0 . "LWPOLYLINE") (100 . "AcDbEntity") (8 . "PLANTS") (62 . 94) (370 . 13) (100 . "AcDbPolyline") (90 . 2) (70 . 0)
(43 . 0.0) (10 19128.9592760181 3435.1435520362) (10 19132.7319004525 3412.5191176471))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19130.842760181 1059.5786199095 0.0) (10 19168.5065186431 1060.5790998904 0.0) (10 19213.7567708648
1049.6856387131 0.0) (10 19226.9966063348 1006.7873303167 0.0))
((0 . "LWPOLYLINE") (100 . "AcDbEntity") (8 . "PLANTS") (62 . 94) (370 . 13) (100 . "AcDbPolyline") (90 . 2) (70 . 0)
(43 . 0.0) (10 19130.842760181 1059.5786199095) (10 19147.8110859729 1040.7239819005))
((0 . "SPLINE") (100 . "AcDbEntity") (8 . "PLANTS") (62 . 94) (370 . 13) (100 . "AcDbSpline") (70 . 0) (71 . 3) (72 . 9)
(73 . 5) (74 . 0) (42 . 0.0000001) (43 . 0.0000001) (40 . 0.0) (40 . 0.0) (40 . 0.0) (40 . 0.0) (40 . 0.617792097) (40 .
1) (40 . 1) (40 . 1) (40 . 1) (10 19132.7319004525 3842.3826923077 0.0) (10 19129.8420917162 3814.1772701157 0.0) (10
19177.8132742581 3788.72244092 0.0) (10 19171.4177058265 3749.0832450572 0.0) (10 19159.1233031674 3733.0316742081 0.0))
((0 . "LWPOLYLINE") (100 . "AcDbEntity") (8 . "PLANTS") (62 . 94) (370 . 13) (100 . "AcDbPolyline") (90 . 2) (70 . 0)
(43 . 0.0) (10 19132.7319004525 3842.3826923077) (10 19140.2714932127 3857.4660633484))
((0 . "LWPOLYLINE") (100 . "AcDbEntity") (8 . "PLANTS") (62 . 94) (370 . 13) (100 . "AcDbPolyline") (90 . 2) (70 . 0)
(43 . 0.0) (10 19132.7319004525 3729.260520362) (10 19151.5837104072 3729.260520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19132.7319004524 3729.260520362 0.0) (10 19108.908449198 3697.767401045 0.0) (10 19124.6012800987
3650.1518095447 0.0) (10 19144.044117647 3619.9095022625 0.0))
((0 . "LWPOLYLINE") (100 . "AcDbEntity") (8 . "PLANTS") (62 . 94) (370 . 13) (100 . "AcDbPolyline") (90 . 2) (70 . 0)
(43 . 0.0) (10 19132.7319004525 3412.5191176471) (10 19140.2714932127 3408.7478506787))
((0 . "LWPOLYLINE") (100 . "AcDbEntity") (8 . "PLANTS") (62 . 94) (370 . 13) (100 . "AcDbPolyline") (90 . 2) (70 . 0)
(43 . 0.0) (10 19144.0441176471 3205.1279411765) (10 19136.4988687783 3223.9819004525))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19200.6052036199 3944.1926470588 0.0) (10 19190.4687724715 3965.8756347061 0.0) (10 19160.7261556634
3966.8377481112 0.0) (10 19140.2714932127 3966.817081448 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19140.2714932127 3966.817081448 0.0) (10 19126.0359570183 3998.6611941209 0.0) (10 19168.246369155
3995.8343490049 0.0) (10 19174.2081447964 4019.6082579186 0.0))
((0 . "LWPOLYLINE") (100 . "AcDbEntity") (8 . "PLANTS") (62 . 94) (370 . 13) (100 . "AcDbPolyline") (90 . 2) (70 . 0)
(43 . 0.0) (10 19140.2714932127 3857.4660633484) (10 19162.8959276018 3857.4660633484))
((0 . "LWPOLYLINE") (100 . "AcDbEntity") (8 . "PLANTS") (62 . 94) (370 . 13) (100 . "AcDbPolyline") (90 . 2) (70 . 0)
(43 . 0.0) (10 19144.0441176471 3619.9095022624) (10 19155.3563348416 3616.1390271493))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19174.2081447964 3495.4751131222 0.0) (10 19184.7340313692 3540.3842880904 0.0) (10 19118.1301182579
3577.0789570396 0.0) (10 19144.044117647 3619.9095022625 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.3597093238)
(40 . 0.528656501) (40 . 1) (40 . 1) (40 . 1) (40 . 1) (10 19204.3721719457 3559.5779411765 0.0) (10 19168.1905095298
3576.4311078149 0.0) (10 19198.9192391887 3610.7093609854 0.0) (10 19157.4411092494 3660.7154194145 0.0) (10
19174.7194994538 3706.8538999214 0.0) (10 19151.5837104073 3729.260520362 0.0))
((0 . "LWPOLYLINE") (100 . "AcDbEntity") (8 . "PLANTS") (62 . 94) (370 . 13) (100 . "AcDbPolyline") (90 . 2) (70 . 0)
(43 . 0.0) (10 19159.1233031674 3733.0316742081) (10 19151.5837104072 3729.260520362))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19159.1233031674 3733.0316742081 0.0) (10 19200.725788614 3750.5399316259 0.0) (10 19198.0300031904
3684.1960065805 0.0) (10 19234.5418552036 3695.3238687783 0.0))
((0 . "SPLINE") (100 . "AcDbEntity") (8 . "PLANTS") (62 . 94) (370 . 13) (100 . "AcDbSpline") (70 . 0) (71 . 3) (72 .
10) (73 . 6) (74 . 0) (42 . 0.0000001) (43 . 0.0000001) (40 . 0.0) (40 . 0.0) (40 . 0.0) (40 . 0.0) (40 . 0.2007204692)
(40 . 0.7124478025) (40 . 1) (40 . 1) (40 . 1) (40 . 1) (10 19162.8959276018 3857.4660633483 0.0) (10 19169.2045753865
3850.0175156132 0.0) (10 19196.3530781102 3829.501942904 0.0) (10 19212.7713801422 3779.2064737335 0.0) (10
19246.218160503 3756.18583765 0.0) (10 19253.3170248869 3744.3438914028 0.0))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19162.8959276018 3857.4660633484 0.0) (10 19175.4634470895 3874.7880209828 0.0) (10 19202.1784572497
3859.4495224261 0.0) (10 19215.6843891403 3876.3193438914 0.0))
((0 . "LWPOLYLINE") (100 . "AcDbEntity") (8 . "PLANTS") (62 . 94) (370 . 13) (100 . "AcDbPolyline") (90 . 3) (70 . 0)
(43 . 0.0) (10 19215.6843891403 3876.3193438914) (10 19204.3680995475 3895.0254524887) (10 19166.6685520362
3914.0271493213))
((0 . "LWPOLYLINE") (100 . "AcDbEntity") (8 . "PLANTS") (62 . 94) (370 . 13) (100 . "AcDbPolyline") (90 . 2) (70 . 0)
(43 . 0.0) (10 19174.2081447964 3495.4751131222) (10 19166.6685520362 3495.4751131222))
((0 . "SPLINE") (100 . "AcDbEntity") (8 . "PLANTS") (62 . 94) (370 . 13) (100 . "AcDbSpline") (70 . 0) (71 . 3) (72 .
11) (73 . 7) (74 . 0) (42 . 0.0000001) (43 . 0.0000001) (40 . 0.0) (40 . 0.0) (40 . 0.0) (40 . 0.0) (40 . 0.0581145541)
(40 . 0.1454136499) (40 . 0.5613630471) (40 . 1) (40 . 1) (40 . 1) (40 . 1) (10 19189.2929864254 3378.5824660633 0.0)
(10 19192.7752376893 3379.8589567144 0.0) (10 19197.2930226528 3383.9778134196 0.0) (10 19190.8383355402 3405.1518815779
0.0) (10 19176.9994651094 3443.4145026727 0.0) (10 19157.6495877899 3476.5631761027 0.0) (10 19166.6685520362
3495.4751131222 0.0))
((0 . "LWPOLYLINE") (100 . "AcDbEntity") (8 . "PLANTS") (62 . 94) (370 . 13) (100 . "AcDbPolyline") (90 . 2) (70 . 0)
(43 . 0.0) (10 19166.6685520362 3144.7963800905) (10 19166.6685520362 3152.3381221719))
((0 . "LWPOLYLINE") (100 . "AcDbEntity") (8 . "PLANTS") (62 . 94) (370 . 13) (100 . "AcDbPolyline") (90 . 2) (70 . 0)
(43 . 0.0) (10 19181.7477375566 4023.3781674208) (10 19174.2081447964 4019.6082579186))
((0 . "LWPOLYLINE") (100 . "AcDbEntity") (8 . "PLANTS") (62 . 94) (370 . 13) (100 . "AcDbPolyline") (90 . 2) (70 . 0)
(43 . 0.0) (10 19174.2081447964 3495.4751131222) (10 19193.0599547511 3484.1628959276))
((0 . "LWPOLYLINE") (100 . "AcDbEntity") (8 . "PLANTS") (62 . 94) (370 . 13) (100 . "AcDbPolyline") (90 . 2) (70 . 0)
(43 . 0.0) (10 19200.6052036199 3944.1926470588) (10 19215.6843891403 3944.1926470588))
((0 . "LWPOLYLINE") (100 . "AcDbEntity") (8 . "PLANTS") (62 . 94) (370 . 13) (100 . "AcDbPolyline") (90 . 3) (70 . 0)
(43 . 0.0) (10 19211.9174208145 3751.8849547511) (10 19233.3363122172 3717.9483031674) (10 19234.5418552036
3695.3238687783))
((0 . "LWPOLYLINE") (100 . "AcDbEntity") (8 . "PLANTS") (62 . 94) (370 . 13) (100 . "AcDbPolyline") (90 . 2) (70 . 0)
(43 . 0.0) (10 19230.7755146649 3416.4309804125) (10 19211.9174208145 3446.4557692308))
((0 . "LWPOLYLINE") (100 . "AcDbEntity") (8 . "PLANTS") (62 . 94) (370 . 13) (100 . "AcDbPolyline") (90 . 3) (70 . 0)
(43 . 0.0) (10 19268.4785067873 3857.4660633484) (10 19238.3088235294 3871.4930995475) (10 19215.6843891403
3876.3193438914))
((0 . "LWPOLYLINE") (100 . "AcDbEntity") (8 . "PLANTS") (62 . 94) (370 . 13) (100 . "AcDbPolyline") (90 . 3) (70 . 0)
(43 . 0.0) (10 19240.0420359636 3624.9277096338) (10 19230.6214932127 3638.7627828054) (10 19215.6843891403 3650.075))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19219.4570135746 957.7686651583 0.0) (10 19219.5426763485 905.3983806138 0.0) (10 19302.8615787013
941.6968337627 0.0) (10 19340.1187782805 942.6838235294 0.0))
((0 . "LWPOLYLINE") (100 . "AcDbEntity") (8 . "PLANTS") (62 . 94) (370 . 13) (100 . "AcDbPolyline") (90 . 2) (70 . 0)
(43 . 0.0) (10 19238.3088235294 3684.0116515837) (10 19234.5418552036 3695.3238687783))
((0 . "LWPOLYLINE") (100 . "AcDbEntity") (8 . "PLANTS") (62 . 94) (370 . 13) (100 . "AcDbPolyline") (90 . 3) (70 . 0)
(43 . 0.0) (10 19272.2454751131 1014.3297511312) (10 19317.4943438914 1014.1813348416) (10 19328.806561086
1010.5571266968))
((0 . "LWPOLYLINE") (100 . "AcDbEntity") (8 . "PLANTS") (62 . 94) (370 . 13) (100 . "AcDbPolyline") (90 . 2) (70 . 0)
(43 . 0.0) (10 19336.3518099548 3766.9683257919) (10 19313.7273755656 3748.1150452489))
((0 . "LWPOLYLINE") (100 . "AcDbEntity") (8 . "PLANTS") (62 . 94) (370 . 13) (100 . "AcDbPolyline") (90 . 2) (70 . 0)
(43 . 0.0) (10 19325.0395927602 3838.6127828054) (10 19321.2669683258 3846.1538461538))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19381.5948488897 3744.3438914027 0.0) (10 19400.3476530716 3830.7457517352 0.0) (10 19326.4732981317
3908.0313697232 0.0) (10 19378.4768724049 3997.6351476422 0.0))
((0 . "LWPOLYLINE") (100 . "AcDbEntity") (8 . "PLANTS") (62 . 94) (370 . 13) (100 . "AcDbPolyline") (90 . 2) (70 . 0)
(43 . 0.0) (10 19385.3713790567 1161.0953023514) (10 19385.3735162507 916.2895927602))
((0 . "LWPOLYLINE") (100 . "AcDbEntity") (8 . "PLANTS") (62 . 94) (370 . 13) (100 . "AcDbPolyline") (90 . 3) (70 . 0)
(43 . 0.0) (10 847.2119909502 3256.7143665158) (10 833.3332579186 3257.7701357466) (10 831.6787478707 3257.085459522))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 838.5689051173 3228.8358148109 0.0) (10 849.873567212 3227.9283593009 0.0) (10 848.976257825
3249.7610029306 0.0) (10 847.2119909502 3256.7143665158 0.0))
((0 . "LWPOLYLINE") (100 . "AcDbEntity") (8 . "PLANTS") (62 . 94) (370 . 13) (100 . "AcDbPolyline") (90 . 3) (70 . 0)
(43 . 0.0) (10 1059.5842760181 394.7227375566) (10 1070.8898190045 394.7227375566) (10 1080.6498941517 384.9632085559))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 1075.6274135908 364.3710382561 0.0) (10 1060.5515216358 362.0185627458 0.0) (10 1041.4282948009
385.0989079187 0.0) (10 1059.5842760181 394.7227375566 0.0))
((0 . "LWPOLYLINE") (100 . "AcDbEntity") (8 . "PLANTS") (62 . 94) (370 . 13) (100 . "AcDbPolyline") (90 . 3) (70 . 0)
(43 . 0.0) (10 2264.3288461538 465.6863122172) (10 2266.2141402715 467.5716063348) (10 2267.2213923104 466.5644147299))
((0 . "LWPOLYLINE") (100 . "AcDbEntity") (8 . "PLANTS") (62 . 94) (370 . 13) (100 . "AcDbPolyline") (90 . 3) (70 . 0)
(43 . 0.0) (10 2266.5602129359 464.1469776417) (10 2266.2141402715 463.8009049774) (10 2264.3288461538 465.6863122172))
((0 . "LWPOLYLINE") (100 . "AcDbEntity") (8 . "PLANTS") (62 . 94) (370 . 13) (100 . "AcDbPolyline") (90 . 4) (70 . 1)
(43 . 0.0) (10 2467.9487556561 1001.1312217195) (10 2469.8340497738 1003.0166289593) (10 2471.7194570136
1001.1312217195) (10 2469.8340497738 999.2458144796))
((0 . "LWPOLYLINE") (100 . "AcDbEntity") (8 . "PLANTS") (62 . 94) (370 . 13) (100 . "AcDbPolyline") (90 . 4) (70 . 1)
(43 . 0.0) (10 2547.1342760181 1266.9683257919) (10 2549.0195701357 1268.8537330317) (10 2550.9049773756
1266.9683257919) (10 2549.0195701357 1265.082918552))
((0 . "LWPOLYLINE") (100 . "AcDbEntity") (8 . "PLANTS") (62 . 94) (370 . 13) (100 . "AcDbPolyline") (90 . 4) (70 . 1)
(43 . 0.0) (10 2771.4932126697 7009.803959276) (10 2773.3786199095 7011.6892533937) (10 2775.2639140271 7009.803959276)
(10 2773.3786199095 7007.9185520362))
((0 . "LWPOLYLINE") (100 . "AcDbEntity") (8 . "PLANTS") (62 . 94) (370 . 13) (100 . "AcDbPolyline") (90 . 4) (70 . 1)
(43 . 0.0) (10 3129.7134615385 6397.0588235294) (10 3131.5987556561 6398.9442307692) (10 3133.4841628959
6397.0588235294) (10 3131.5987556561 6395.1734162896))
((0 . "LWPOLYLINE") (100 . "AcDbEntity") (8 . "PLANTS") (62 . 94) (370 . 13) (100 . "AcDbPolyline") (90 . 4) (70 . 1)
(43 . 0.0) (10 3135.3695701357 6623.3031674208) (10 3137.2548642534 6625.1885746606) (10 3139.1402714932
6623.3031674208) (10 3137.2548642534 6621.417760181))
((0 . "LWPOLYLINE") (100 . "AcDbEntity") (8 . "PLANTS") (62 . 94) (370 . 13) (100 . "AcDbPolyline") (90 . 4) (70 . 1)
(43 . 0.0) (10 3271.1161764706 746.6063348416) (10 3273.0014705882 748.4917420814) (10 3274.8868778281 746.6063348416)
(10 3273.0014705882 744.7209276018))
((0 . "LWPOLYLINE") (100 . "AcDbEntity") (8 . "PLANTS") (62 . 94) (370 . 13) (100 . "AcDbPolyline") (90 . 4) (70 . 1)
(43 . 0.0) (10 4061.0859728507 345.0226244344) (10 4062.9713800905 346.9080316742) (10 4064.8566742081 345.0226244344)
(10 4062.9713800905 343.1372171946))
((0 . "LWPOLYLINE") (100 . "AcDbEntity") (8 . "PLANTS") (62 . 94) (370 . 13) (100 . "AcDbPolyline") (90 . 4) (70 . 1)
(43 . 0.0) (10 4155.3544117647 6977.75260181) (10 4157.2398190045 6979.6380090498) (10 4159.1252262443 6977.75260181)
(10 4157.2398190045 6975.8673076923))
((0 . "LWPOLYLINE") (100 . "AcDbEntity") (8 . "PLANTS") (62 . 94) (370 . 13) (100 . "AcDbPolyline") (90 . 4) (70 . 1)
(43 . 0.0) (10 4277.9035067873 4223.2277149321) (10 4279.788800905 4225.1131221719) (10 4281.6742081448 4223.2277149321)
(10 4279.788800905 4221.3424208145))
((0 . "SPLINE") (100 . "AcDbEntity") (8 . "PLANTS") (62 . 94) (370 . 13) (100 . "AcDbSpline") (70 . 3) (71 . 3) (72 .
11) (73 . 7) (74 . 0) (42 . 0.0000001) (43 . 0.0000001) (40 . -0.6153629812) (40 . -0.468639682) (40 . -0.191171749) (40
. 0.0) (40 . 0.3846370188) (40 . 0.531360318) (40 . 0.808828251) (40 . 1) (40 . 1.3846370188) (40 . 1.531360318) (40 .
1.808828251) (10 4392.6564390618 3472.28410139 0.0) (10 4365.0495309354 3471.3414978613 0.0) (10 4386.6700861014
3498.9988644043 0.0) (10 4401.6029035175 3491.7910135002 0.0) (10 4392.6564390618 3472.28410139 0.0) (10 4365.0495309354
3471.3414978613 0.0) (10 4386.6700861014 3498.9988644043 0.0))
((0 . "LWPOLYLINE") (100 . "AcDbEntity") (8 . "PLANTS") (62 . 94) (370 . 13) (100 . "AcDbPolyline") (90 . 4) (70 . 1)
(43 . 0.0) (10 4651.2066742081 3840.4977375566) (10 4653.0919683258 3842.3831447964) (10 4654.9773755656
3840.4977375566) (10 4653.0919683258 3838.6123303167))
((0 . "LWPOLYLINE") (100 . "AcDbEntity") (8 . "PLANTS") (62 . 94) (370 . 13) (100 . "AcDbPolyline") (90 . 4) (70 . 1)
(43 . 0.0) (10 4681.3725113122 3842.3831447964) (10 4683.257918552 3844.268438914) (10 4685.1433257919 3842.3831447964)
(10 4683.257918552 3840.4977375566))
((0 . "LWPOLYLINE") (100 . "AcDbEntity") (8 . "PLANTS") (62 . 94) (370 . 13) (100 . "AcDbPolyline") (90 . 4) (70 . 1)
(43 . 0.0) (10 4913.2729638009 3995.0980769231) (10 4915.1583710407 3996.9833710407) (10 4917.0437782805
3995.0980769231) (10 4915.1583710407 3993.2126696833))
((0 . "LWPOLYLINE") (100 . "AcDbEntity") (8 . "PLANTS") (62 . 94) (370 . 13) (100 . "AcDbPolyline") (90 . 4) (70 . 1)
(43 . 0.0) (10 4935.89739819 1093.5143665158) (10 4937.7828054299 1095.3996606335) (10 4939.6682126697 1093.5143665158)
(10 4937.7828054299 1091.628959276))
((0 . "SPLINE") (100 . "AcDbEntity") (8 . "PLANTS") (62 . 94) (370 . 13) (100 . "AcDbSpline") (70 . 3) (71 . 3) (72 .
11) (73 . 7) (74 . 0) (42 . 0.0000001) (43 . 0.0000001) (40 . -0.8313470404) (40 . -0.5160223656) (40 . -0.2367467158)
(40 . 0.0) (40 . 0.1686529596) (40 . 0.4839776344) (40 . 0.7632532842) (40 . 1) (40 . 1.1686529596) (40 . 1.4839776344)
(40 . 1.7632532842) (10 4964.8098889163 3547.3703329395 0.0) (10 4958.282771094 3595.0169086007 0.0) (10 4915.956043958
3586.7019682259 0.0) (10 4910.1603549134 3530.7107148144 0.0) (10 4964.8098889163 3547.3703329395 0.0) (10
4958.282771094 3595.0169086007 0.0) (10 4915.956043958 3586.7019682259 0.0))
((0 . "SPLINE") (100 . "AcDbEntity") (8 . "PLANTS") (62 . 94) (370 . 13) (100 . "AcDbSpline") (70 . 3) (71 . 3) (72 .
11) (73 . 7) (74 . 0) (42 . 0.0000001) (43 . 0.0000001) (40 . -0.7029600404) (40 . -0.5475902784) (40 . -0.3444156216)
(40 . 0.0) (40 . 0.2970399596) (40 . 0.4524097216) (40 . 0.6555843784) (40 . 1) (40 . 1.2970399596) (40 . 1.4524097216)
(40 . 1.6555843784) (10 5224.7812203432 388.3556393288 0.0) (10 5149.5267838726 357.9533442927 0.0) (10 5168.940224852
424.227954107 0.0) (10 5205.5647680223 425.5124871811 0.0) (10 5224.7812203432 388.3556393288 0.0) (10 5149.5267838726
357.9533442927 0.0) (10 5168.940224852 424.227954107 0.0))
((0 . "LWPOLYLINE") (100 . "AcDbEntity") (8 . "PLANTS") (62 . 94) (370 . 13) (100 . "AcDbPolyline") (90 . 4) (70 . 1)
(43 . 0.0) (10 5250.7541855204 3921.5686651584) (10 5252.639479638 3923.453959276) (10 5254.5248868778 3921.5686651584)
(10 5252.639479638 3919.6832579186))
((0 . "LWPOLYLINE") (100 . "AcDbEntity") (8 . "PLANTS") (62 . 94) (370 . 13) (100 . "AcDbPolyline") (90 . 4) (70 . 1)
(43 . 0.0) (10 5294.1176470588 267.7225113122) (10 5296.0030542986 269.6078054299) (10 5297.8883484163 267.7225113122)
(10 5296.0030542986 265.8371040724))
((0 . "SPLINE") (100 . "AcDbEntity") (8 . "PLANTS") (62 . 94) (370 . 13) (100 . "AcDbSpline") (70 . 3) (71 . 3) (72 .
10) (73 . 6) (74 . 0) (42 . 0.0000001) (43 . 0.0000001) (40 . -1) (40 . -0.530497105) (40 . -0.4311381486) (40 . 0.0)
(40 . 0.469502895) (40 . 0.5688618514) (40 . 1) (40 . 1.469502895) (40 . 1.5688618514) (40 . 2) (10 5677.2374376792
4038.5723988799 0.0) (10 5634.101463905 4065.727190723 0.0) (10 5653.7851613381 4014.7946195386 0.0) (10 5677.2374376792
4038.5723988799 0.0) (10 5634.101463905 4065.727190723 0.0) (10 5653.7851613381 4014.7946195386 0.0))
((0 . "LWPOLYLINE") (100 . "AcDbEntity") (8 . "PLANTS") (62 . 94) (370 . 13) (100 . "AcDbPolyline") (90 . 4) (70 . 1)
(43 . 0.0) (10 5782.4283936652 296.0030542986) (10 5784.3136877828 297.8883484163) (10 5786.1990950226 296.0030542986)
(10 5784.3136877828 294.1176470588))
((0 . "LWPOLYLINE") (100 . "AcDbEntity") (8 . "PLANTS") (62 . 94) (370 . 13) (100 . "AcDbPolyline") (90 . 4) (70 . 1)
(43 . 0.0) (10 5901.2066742081 1057.6923076923) (10 5903.0919683258 1059.5777149321) (10 5904.9773755656
1057.6923076923) (10 5903.0919683258 1055.8069004525))
((0 . "LWPOLYLINE") (100 . "AcDbEntity") (8 . "PLANTS") (62 . 94) (370 . 13) (100 . "AcDbPolyline") (90 . 4) (70 . 1)
(43 . 0.0) (10 5997.360520362 3944.1930995475) (10 5999.2458144796 3946.0783936652) (10 6001.1312217195 3944.1930995475)
(10 5999.2458144796 3942.3076923077))
((0 . "SPLINE") (100 . "AcDbEntity") (8 . "PLANTS") (62 . 94) (370 . 13) (100 . "AcDbSpline") (70 . 3) (71 . 3) (72 .
14) (73 . 10) (74 . 0) (42 . 0.0000001) (43 . 0.0000001) (40 . -0.3773442611) (40 . -0.2541013443) (40 . -0.054714662)
(40 . 0.0) (40 . 0.0590578744) (40 . 0.2531465879) (40 . 0.4797575575) (40 . 0.6226557389) (40 . 0.7458986557) (40 .
0.945285338) (40 . 1) (40 . 1.0590578744) (40 . 1.2531465879) (40 . 1.4797575575) (10 6094.0563907576 3569.9810361766
0.0) (10 6085.9979926817 3577.9520912334 0.0) (10 6074.6648888264 3576.7893458833 0.0) (10 6054.9468133599
3554.966163721 0.0) (10 6057.4363481515 3524.0833797159 0.0) (10 6081.8471988527 3527.4380105577 0.0) (10
6094.6551077613 3546.4893180545 0.0) (10 6094.0563907576 3569.9810361766 0.0) (10 6085.9979926817 3577.9520912334 0.0)
(10 6074.6648888264 3576.7893458833 0.0))
((0 . "LWPOLYLINE") (100 . "AcDbEntity") (8 . "PLANTS") (62 . 94) (370 . 13) (100 . "AcDbPolyline") (90 . 4) (70 . 1)
(43 . 0.0) (10 6133.1071266968 3785.8220588235) (10 6134.9924208145 3787.7073529412) (10 6136.8778280543
3785.8220588235) (10 6134.9924208145 3783.9366515837))
((0 . "LWPOLYLINE") (100 . "AcDbEntity") (8 . "PLANTS") (62 . 94) (370 . 13) (100 . "AcDbPolyline") (90 . 4) (70 . 1)
(43 . 0.0) (10 6148.1900452489 3403.0919683258) (10 6150.0754524887 3404.9773755656) (10 6151.9607466063
3403.0919683258) (10 6150.0754524887 3401.2066742081))
((0 . "LWPOLYLINE") (100 . "AcDbEntity") (8 . "PLANTS") (62 . 94) (370 . 13) (100 . "AcDbPolyline") (90 . 4) (70 . 1)
(43 . 0.0) (10 6587.4811085973 1114.2533936652) (10 6589.3665158371 1116.138800905) (10 6591.2519230769 1114.2533936652)
(10 6589.3665158371 1112.3679864253))
((0 . "LWPOLYLINE") (100 . "AcDbEntity") (8 . "PLANTS") (62 . 94) (370 . 13) (100 . "AcDbPolyline") (90 . 4) (70 . 1)
(43 . 0.0) (10 6800.5279411765 460.0302036199) (10 6802.4132352941 461.9154977376) (10 6804.2986425339 460.0302036199)
(10 6802.4132352941 458.1447963801))
((0 . "LWPOLYLINE") (100 . "AcDbEntity") (8 . "PLANTS") (62 . 94) (370 . 13) (100 . "AcDbPolyline") (90 . 4) (70 . 1)
(43 . 0.0) (10 7320.8899321267 708.8989819005) (10 7322.7752262443 710.7842760181) (10 7324.6606334842 708.8989819005)
(10 7322.7752262443 707.0135746606))
((0 . "LWPOLYLINE") (100 . "AcDbEntity") (8 . "PLANTS") (62 . 94) (370 . 13) (100 . "AcDbPolyline") (90 . 4) (70 . 1)
(43 . 0.0) (10 7765.8371040724 6806.1840497738) (10 7767.7225113122 6808.0693438914) (10 7769.6078054299
6806.1840497738) (10 7767.7225113122 6804.2986425339))
((0 . "LWPOLYLINE") (100 . "AcDbEntity") (8 . "PLANTS") (62 . 94) (370 . 13) (100 . "AcDbPolyline") (90 . 4) (70 . 1)
(43 . 0.0) (10 12320.8899321267 7023.0014705882) (10 12322.7752262443 7024.8868778281) (10 12324.6606334842
7023.0014705882) (10 12322.7752262443 7021.1161764706))
((0 . "LWPOLYLINE") (100 . "AcDbEntity") (8 . "PLANTS") (62 . 94) (370 . 13) (100 . "AcDbPolyline") (90 . 4) (70 . 1)
(43 . 0.0) (10 12332.2021493213 388.3860859729) (10 12334.0874434389 390.2714932127) (10 12335.9728506787
388.3860859729) (10 12334.0874434389 386.5007918552))
((0 . "LWPOLYLINE") (100 . "AcDbEntity") (8 . "PLANTS") (62 . 94) (370 . 13) (100 . "AcDbPolyline") (90 . 4) (70 . 1)
(43 . 0.0) (10 12941.1764705882 6694.9471719457) (10 12943.0618778281 6696.8325791855) (10 12944.9471719457
6694.9471719457) (10 12943.0618778281 6693.0618778281))
((0 . "SPLINE") (100 . "AcDbEntity") (8 . "PLANTS") (62 . 94) (370 . 13) (100 . "AcDbSpline") (70 . 3) (71 . 3) (72 .
10) (73 . 6) (74 . 0) (42 . 0.0000001) (43 . 0.0000001) (40 . -1) (40 . -0.5510411243) (40 . -0.22742075) (40 . 0.0) (40
. 0.4489588757) (40 . 0.77257925) (40 . 1) (40 . 1.4489588757) (40 . 1.77257925) (40 . 2) (10 13136.4915164829
6550.3782173061 0.0) (10 13110.2063215891 6557.1289340352 0.0) (10 13130.6786303299 6520.8088607428 0.0) (10
13136.4915164829 6550.3782173061 0.0) (10 13110.2063215891 6557.1289340352 0.0) (10 13130.6786303299 6520.8088607428
0.0))
((0 . "LWPOLYLINE") (100 . "AcDbEntity") (8 . "PLANTS") (62 . 94) (370 . 13) (100 . "AcDbPolyline") (90 . 4) (70 . 1)
(43 . 0.0) (10 13214.5550904977 3897.0588235294) (10 13216.4403846154 3898.9442307692) (10 13218.3257918552
3897.0588235294) (10 13216.4403846154 3895.1734162896))
((0 . "LWPOLYLINE") (100 . "AcDbEntity") (8 . "PLANTS") (62 . 94) (370 . 13) (100 . "AcDbPolyline") (90 . 4) (70 . 1)
(43 . 0.0) (10 13363.4992081448 4012.0664027149) (10 13365.3846153846 4013.9516968326) (10 13367.2700226244
4012.0664027149) (10 13365.3846153846 4010.1809954751))
((0 . "LWPOLYLINE") (100 . "AcDbEntity") (8 . "PLANTS") (62 . 94) (370 . 13) (100 . "AcDbPolyline") (90 . 4) (70 . 1)
(43 . 0.0) (10 13606.7118778281 3695.324321267) (10 13608.5972850679 3697.2096153846) (10 13610.4826923077
3695.324321267) (10 13608.5972850679 3693.4389140271))
((0 . "LWPOLYLINE") (100 . "AcDbEntity") (8 . "PLANTS") (62 . 94) (370 . 13) (100 . "AcDbPolyline") (90 . 4) (70 . 1)
(43 . 0.0) (10 13927.2247737557 371.417760181) (10 13929.1100678733 373.3031674208) (10 13930.9954751131 371.417760181)
(10 13929.1100678733 369.5324660633))
((0 . "SPLINE") (100 . "AcDbEntity") (8 . "PLANTS") (62 . 94) (370 . 13) (100 . "AcDbSpline") (70 . 3) (71 . 3) (72 .
12) (73 . 8) (74 . 0) (42 . 0.0000001) (43 . 0.0000001) (40 . -0.6214863329) (40 . -0.4708519461) (40 . -0.1789810167)
(40 . 0.0) (40 . 0.2435623639) (40 . 0.3785136671) (40 . 0.5291480539) (40 . 0.8210189833) (40 . 1) (40 . 1.2435623639)
(40 . 1.3785136671) (40 . 1.5291480539) (10 14130.5680582167 1049.2892217821 0.0) (10 14099.6981588189 1014.8863020979
0.0) (10 14076.1600203379 1046.527564476 0.0) (10 14086.2870087487 1075.9503688454 0.0) (10 14113.938356747
1087.2014960702 0.0) (10 14130.5680582167 1049.2892217821 0.0) (10 14099.6981588189 1014.8863020979 0.0) (10
14076.1600203379 1046.527564476 0.0))
((0 . "LWPOLYLINE") (100 . "AcDbEntity") (8 . "PLANTS") (62 . 94) (370 . 13) (100 . "AcDbPolyline") (90 . 4) (70 . 1)
(43 . 0.0) (10 14200.603280543 265.8371040724) (10 14202.4886877828 267.7225113122) (10 14204.3740950226 265.8371040724)
(10 14202.4886877828 263.9516968326))
((0 . "LWPOLYLINE") (100 . "AcDbEntity") (8 . "PLANTS") (62 . 94) (370 . 13) (100 . "AcDbPolyline") (90 . 4) (70 . 1)
(43 . 0.0) (10 14279.788800905 3819.7587104072) (10 14281.6742081448 3821.6440045249) (10 14283.5596153846
3819.7587104072) (10 14281.6742081448 3817.8733031674))
((0 . "LWPOLYLINE") (100 . "AcDbEntity") (8 . "PLANTS") (62 . 94) (370 . 13) (100 . "AcDbPolyline") (90 . 4) (70 . 1)
(43 . 0.0) (10 15073.5294117647 3676.4705882353) (10 15075.4148190045 3678.3559954751) (10 15077.3001131222
3676.4705882353) (10 15075.4148190045 3674.5851809955))
((0 . "LWPOLYLINE") (100 . "AcDbEntity") (8 . "PLANTS") (62 . 94) (370 . 13) (100 . "AcDbPolyline") (90 . 4) (70 . 1)
(43 . 0.0) (10 15180.9954751131 296.0030542986) (10 15182.8808823529 297.8883484163) (10 15184.7661764706
296.0030542986) (10 15182.8808823529 294.1176470588))
((0 . "LWPOLYLINE") (100 . "AcDbEntity") (8 . "PLANTS") (62 . 94) (370 . 13) (100 . "AcDbPolyline") (90 . 4) (70 . 1)
(43 . 0.0) (10 15388.3860859729 3897.0588235294) (10 15390.2714932127 3898.9442307692) (10 15392.1569004525
3897.0588235294) (10 15390.2714932127 3895.1734162896))
((0 . "LWPOLYLINE") (100 . "AcDbEntity") (8 . "PLANTS") (62 . 94) (370 . 13) (100 . "AcDbPolyline") (90 . 4) (70 . 1)
(43 . 0.0) (10 15524.1326923077 3661.3876696833) (10 15526.0180995475 3663.2729638009) (10 15527.9035067873
3661.3876696833) (10 15526.0180995475 3659.5022624434))
((0 . "LWPOLYLINE") (100 . "AcDbEntity") (8 . "PLANTS") (62 . 94) (370 . 13) (100 . "AcDbPolyline") (90 . 4) (70 . 1)
(43 . 0.0) (10 16676.0935520362 761.6892533937) (10 16677.9788461538 763.5746606335) (10 16679.8642533937
761.6892533937) (10 16677.9788461538 759.803959276))
((0 . "SPLINE") (100 . "AcDbEntity") (8 . "PLANTS") (62 . 94) (370 . 13) (100 . "AcDbSpline") (70 . 3) (71 . 3) (72 .
11) (73 . 7) (74 . 0) (42 . 0.0000001) (43 . 0.0000001) (40 . -0.7561300881) (40 . -0.5921187239) (40 . -0.3278983955)
(40 . 0.0) (40 . 0.2438699119) (40 . 0.4078812761) (40 . 0.6721016045) (40 . 1) (40 . 1.2438699119) (40 . 1.4078812761)
(40 . 1.6721016045) (10 16895.9580145507 6618.115613387 0.0) (10 16936.3080528228 6618.4185583266 0.0) (10
16928.9760907763 6649.1886629741 0.0) (10 16908.1863234691 6648.7156868347 0.0) (10 16895.9580145507 6618.115613387 0.0)
(10 16936.3080528228 6618.4185583266 0.0) (10 16928.9760907763 6649.1886629741 0.0))
((0 . "LWPOLYLINE") (100 . "AcDbEntity") (8 . "PLANTS") (62 . 94) (370 . 13) (100 . "AcDbPolyline") (90 . 4) (70 . 1)
(43 . 0.0) (10 17004.1478506787 7045.6259049774) (10 17006.0331447964 7047.5113122172) (10 17007.9185520362
7045.6259049774) (10 17006.0331447964 7043.7406108597))
((0 . "LWPOLYLINE") (100 . "AcDbEntity") (8 . "PLANTS") (62 . 94) (370 . 13) (100 . "AcDbPolyline") (90 . 4) (70 . 1)
(43 . 0.0) (10 17173.8311085973 411.010520362) (10 17175.7164027149 412.8959276018) (10 17177.6018099548 411.010520362)
(10 17175.7164027149 409.1252262443))
((0 . "LWPOLYLINE") (100 . "AcDbEntity") (8 . "PLANTS") (62 . 94) (370 . 13) (100 . "AcDbPolyline") (90 . 4) (70 . 1)
(43 . 0.0) (10 17664.0271493213 3723.6048642534) (10 17665.9125565611 3725.490158371) (10 17667.7978506787
3723.6048642534) (10 17665.9125565611 3721.7194570136))
((0 . "LWPOLYLINE") (100 . "AcDbEntity") (8 . "PLANTS") (62 . 94) (370 . 13) (100 . "AcDbPolyline") (90 . 4) (70 . 1)
(43 . 0.0) (10 17669.6832579186 3559.5777149321) (10 17671.5686651584 3561.4630090498) (10 17673.453959276
3559.5777149321) (10 17671.5686651584 3557.6923076923))
((0 . "LWPOLYLINE") (100 . "AcDbEntity") (8 . "PLANTS") (62 . 94) (370 . 13) (100 . "AcDbPolyline") (90 . 4) (70 . 1)
(43 . 0.0) (10 17714.9321266968 3482.2774886878) (10 17716.8175339367 3484.1628959276) (10 17718.7028280543
3482.2774886878) (10 17716.8175339367 3480.3921945701))
((0 . "LWPOLYLINE") (100 . "AcDbEntity") (8 . "PLANTS") (62 . 94) (370 . 13) (100 . "AcDbPolyline") (90 . 4) (70 . 1)
(43 . 0.0) (10 18508.6727375566 3804.675678733) (10 18510.5580316742 3806.5610859729) (10 18512.443438914
3804.675678733) (10 18510.5580316742 3802.7903846154))
((0 . "LWPOLYLINE") (100 . "AcDbEntity") (8 . "PLANTS") (62 . 94) (370 . 13) (100 . "AcDbPolyline") (90 . 4) (70 . 1)
(43 . 0.0) (10 18808.4464932127 3214.5550904977) (10 18810.3317873303 3216.4403846154) (10 18812.2171945701
3214.5550904977) (10 18810.3317873303 3212.6696832579))
((0 . "SPLINE") (100 . "AcDbEntity") (8 . "PLANTS") (62 . 94) (370 . 13) (100 . "AcDbSpline") (70 . 3) (71 . 3) (72 .
13) (73 . 9) (74 . 0) (42 . 0.0000001) (43 . 0.0000001) (40 . -0.4961544274) (40 . -0.3770280065) (40 . -0.0950237258)
(40 . 0.0) (40 . 0.1025447249) (40 . 0.2827802627) (40 . 0.5038455726) (40 . 0.6229719935) (40 . 0.9049762742) (40 . 1)
(40 . 1.1025447249) (40 . 1.2827802627) (40 . 1.5038455726) (10 19075.0300147575 1117.9053876469 0.0) (10
19053.2067367218 1138.8555901271 0.0) (10 19069.7012841904 1157.3200404327 0.0) (10 19100.9390690097 1167.6385548517
0.0) (10 19136.1336173014 1148.1231080105 0.0) (10 19115.2004629104 1116.8367857375 0.0) (10 19075.0300147575
1117.9053876469 0.0) (10 19053.2067367218 1138.8555901271 0.0) (10 19069.7012841904 1157.3200404327 0.0))
((0 . "SPLINE") (100 . "AcDbEntity") (8 . "PLANTS") (62 . 94) (370 . 13) (100 . "AcDbSpline") (70 . 3) (71 . 3) (72 .
10) (73 . 6) (74 . 0) (42 . 0.0000001) (43 . 0.0000001) (40 . -1) (40 . -0.7214050095) (40 . -0.4505209982) (40 . 0.0)
(40 . 0.2785949905) (40 . 0.5494790018) (40 . 1) (40 . 1.2785949905) (40 . 1.5494790018) (40 . 2) (10 19127.3804227284
3253.0632247852 0.0) (10 19093.2270996528 3300.490893568 0.0) (10 19141.3560268888 3297.3554911183 0.0) (10
19127.3804227284 3253.0632247852 0.0) (10 19093.2270996528 3300.490893568 0.0) (10 19141.3560268888 3297.3554911183
0.0))
((0 . "LWPOLYLINE") (100 . "AcDbEntity") (8 . "PLANTS") (62 . 94) (370 . 13) (100 . "AcDbPolyline") (90 . 4) (70 . 1)
(43 . 0.0) (10 19198.7179864253 3661.3876696833) (10 19200.603280543 3663.2729638009) (10 19202.4886877828
3661.3876696833) (10 19200.603280543 3659.5022624434))
((0 . "LWPOLYLINE") (100 . "AcDbEntity") (8 . "PLANTS") (62 . 94) (370 . 13) (100 . "AcDbPolyline") (90 . 4) (70 . 1)
(43 . 0.0) (10 19200.603280543 3470.9652714932) (10 19202.4886877828 3472.850678733) (10 19204.3740950226
3470.9652714932) (10 19202.4886877828 3469.0799773756))
((0 . "LWPOLYLINE") (100 . "AcDbEntity") (8 . "PLANTS") (62 . 94) (370 . 13) (100 . "AcDbPolyline") (90 . 3) (70 . 0)
(43 . 0.0) (10 19205.5777149321 3558.3737556561) (10 19219.4570135747 3558.5214932127) (10 19236.5216984126
3545.7201147365))
((0 . "SPLINE") (100 . "AcDbEntity") (8 . "PLANTS") (62 . 94) (370 . 13) (100 . "AcDbSpline") (70 . 0) (71 . 3) (72 . 8)
(73 . 4) (74 . 0) (42 . 0.0000001) (43 . 0.0000001) (40 . 0.0) (40 . 0.0) (40 . 0.0) (40 . 0.0) (40 . 1) (40 . 1) (40 .
1) (40 . 1) (10 19235.2537173854 3517.1905416235 0.0) (10 19216.9129970364 3513.5022384013 0.0) (10 19200.722572279
3541.4466623484 0.0) (10 19205.5777149321 3558.3737556561 0.0))
))
(setq F2:LAYERS '("ARCH" "GLASS" "GROUND" "LOUVERS" "MASONRY" "PLANTS" "SOLAR" "WINDOWS"))
(setq F2:BLOCK "FACADE2_95AC1B2133")

(defun F2:BUILD (name / row)
  (entmake (list '(0 . "BLOCK") '(100 . "AcDbEntity") '(8 . "0")
    '(100 . "AcDbBlockBegin") (cons 2 name) '(70 . 0)
    '(10 0.0 0.0 0.0) (cons 3 name) '(1 . "")))
  (foreach row F2:DATA (entmake row))
  (entmake '((0 . "ENDBLK") (100 . "AcDbEntity") (8 . "0")
    (100 . "AcDbBlockEnd"))))
(defun c:FACADE2 (/ point width factor name)
  (setq point (getpoint "\nInsertion point: "))
  (if point
    (progn
      (initget 6)
      (setq width (getreal "\nEstimated baseline width in millimetres <20000>: "))
      (if (null width) (setq width 20000.0))
      (setq factor (/ width 20000.0))
      (foreach name F2:LAYERS
        (if (null (tblsearch "LAYER" name))
          (entmake (list '(0 . "LAYER") '(100 . "AcDbSymbolTableRecord")
            '(100 . "AcDbLayerTableRecord") (cons 2 name) '(70 . 0)
            (cons 62 (if (= name "PLANTS") 94 7)) '(6 . "Continuous") '(370 . 13)))))
      (if (null (tblsearch "BLOCK" F2:BLOCK)) (F2:BUILD F2:BLOCK))
      (entmake (list '(0 . "INSERT") '(100 . "AcDbEntity") '(8 . "0")
        '(100 . "AcDbBlockReference") (cons 2 F2:BLOCK)
        (cons 10 (trans point 1 0)) (cons 41 factor) (cons 42 factor)
        (cons 43 factor) '(50 . 0.0)))
      (princ "\nInserted geometric facade. EXPLODE for individual entities.")))
  (princ))
(princ "\nLoaded. Run FACADE2.")
(princ)
