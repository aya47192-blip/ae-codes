; palace_facade_clean.lsp -- self-contained clean facade reconstruction
; Units: millimetres. Nominal facade width: 14000 (ESTIMATED, NOT SURVEYED).
; AutoCAD for Windows with Visual LISP/ActiveX. Load with APPLOAD; run PALACE.
; Shared edges occur once. Closed contours may contain connected junction-to-junction chains.
; All visible facade entities: RGB black, physical lineweight 0.18 mm.
; No external DXF, image, Python, network, or package is required to draw this data.
; Native dimension creation uses AutoCAD ActiveX; this environment could not execute AutoCAD.
(vl-load-com)

(defun PALC:emit (data)
  (if (null (entmake data))
    (progn (princ "\nPALACE: AutoCAD rejected an entity; undo this operation if necessary.") (quit))))

(defun PALC:layer (name white / full)
  (setq full (strcat "PALC_" name))
  (if (null (tblsearch "LAYER" full))
    (PALC:emit
      (list '(0 . "LAYER") '(100 . "AcDbSymbolTableRecord")
            '(100 . "AcDbLayerTableRecord") (cons 2 full) '(70 . 0)
            '(62 . 7) '(6 . "Continuous") '(370 . 18)
            (cons 420 (if white 16777215 0)))))
  full)

(defun PALC:poly (row / pts)
  (setq pts (caddr row))
  (PALC:emit
    (append
      (list '(0 . "LWPOLYLINE") '(100 . "AcDbEntity")
            (cons 8 (strcat "PALC_" (car row))) '(62 . 7) '(420 . 0) '(370 . 18) '(6 . "Continuous")
            '(100 . "AcDbPolyline") (cons 90 (length pts)) (cons 70 (cadr row))
            '(38 . 0.0) '(43 . 0.0))
      (mapcar '(lambda (p) (cons 10 p)) pts))))

(defun PALC:build (name / row)
  (PALC:emit
    (list '(0 . "BLOCK") '(100 . "AcDbEntity") '(8 . "0")
          '(100 . "AcDbBlockBegin") (cons 2 name) '(70 . 0) '(10 0.0 0.0 0.0) (cons 3 name) '(1 . "")))
  (PALC:emit
    (list '(0 . "SOLID") '(100 . "AcDbEntity") '(8 . "PALC_00_WHITE_BACKGROUND")
          '(62 . 7) '(420 . 16777215) '(370 . 18) '(100 . "AcDbTrace")
          '(10 -2000.0 -1200.0 0.0) '(11 16000.0 -1200.0 0.0)
          '(12 -2000.0 12410.687 0.0) '(13 16000.0 12410.687 0.0)))
  (foreach row PALC:DATA (PALC:poly row))
  (PALC:emit '((0 . "ENDBLK") (100 . "AcDbEntity") (8 . "0") (100 . "AcDbBlockEnd"))))

(defun PALC:point (xy base factor)
  (list (+ (car base) (* factor (car xy)))
        (+ (cadr base) (* factor (cadr xy))) (caddr base)))

(defun PALC:property (obj name value)
  (if (vlax-property-available-p obj name T)
    (vlax-put-property obj name value)))

(defun PALC:dimension (space row base factor / obj colour item)
  (setq obj
    (vla-AddDimRotated space
      (vlax-3d-point (PALC:point (nth 0 row) base factor))
      (vlax-3d-point (PALC:point (nth 1 row) base factor))
      (vlax-3d-point (PALC:point (nth 2 row) base factor))
      (nth 3 row)))
  (vla-put-Layer obj "PALC_09_ESTIMATED_DIMS")
  (vla-put-Lineweight obj 18)
  (setq colour (vla-get-TrueColor obj))
  (vla-SetRGB colour 0 0 0)
  (vla-put-TrueColor obj colour)
  (vlax-release-object colour)
  (foreach item
    (list (cons 'TextHeight (* factor 145.0))
          (cons 'ArrowheadSize (* factor 100.0))
          (cons 'ExtensionLineOffset (* factor 75.0))
          (cons 'ExtensionLineExtend (* factor 65.0))
          (cons 'DimensionLineWeight 18) (cons 'ExtensionLineWeight 18)
          (cons 'DimensionLineColor 0) (cons 'ExtensionLineColor 0) (cons 'TextColor 0)
          (cons 'PrimaryUnitsPrecision 0) (cons 'LinearScaleFactor 1.0) (cons 'ScaleFactor 1.0)
          (cons 'Arrowhead1Type 0) (cons 'Arrowhead2Type 0)
          (cons 'DimLine1Suppress 0) (cons 'DimLine2Suppress 0)
          (cons 'ExtLine1Suppress 0) (cons 'ExtLine2Suppress 0)
          (cons 'DimensionLinetype "Continuous") (cons 'ExtLine1Linetype "Continuous") (cons 'ExtLine2Linetype "Continuous")
          (cons 'UnitsFormat 2) (cons 'TextOverride "<> mm (est.)"))
    (PALC:property obj (car item) (cdr item)))
  (vla-Update obj)
  (vlax-vla-object->ename obj))

(defun PALC:dimensions (record / acad doc space row old result base factor)
  (setq acad (vlax-get-acad-object) doc (vla-get-ActiveDocument acad)
        space (vla-get-ModelSpace doc) base (cadr record) factor (caddr record))
  ; Re-running PALACEDIMS replaces only dimensions tracked for this last insertion.
  (foreach old (cadddr record) (if (entget old) (entdel old)))
  (setq result nil)
  (foreach row PALC:DIMS
    (setq result (cons (PALC:dimension space row base factor) result)))
  (list (car record) base factor (reverse result)))

(defun c:PALACE (/ *error* acad doc mark base factor width name count entity oldlast dims row)
  (setq acad (vlax-get-acad-object) doc (vla-get-ActiveDocument acad)
        oldlast PALC:LAST mark nil entity nil)
  (defun *error* (message)
    (if mark (vl-catch-all-apply 'vla-EndUndoMark (list doc)))
    (setq PALC:LAST oldlast)
    (if (not (wcmatch (strcase message) "*CANCEL*,*QUIT*,*BREAK*"))
      (princ (strcat "\nPALACE error: " message)))
    (princ "\nIf an operation was interrupted, UNDO once removes its new drawing objects.")
    (princ))
  (princ "\nPALACE: estimated geometry in mm. Recommended: use a new blank drawing.")
  (setq base (getpoint "\nPick the ground-datum insertion point: "))
  (if base
    (progn
      (setq base (trans base 1 0))
      (initget 6)
      (setq width (getdist "\nEstimated overall facade width in mm <14000>: "))
      (if (null width) (setq width 14000.0))
      (setq factor (/ width 14000.0))
      (vla-StartUndoMark doc) (setq mark T)
      (PALC:layer "00_WHITE_BACKGROUND" T)
      (foreach row PALC:LAYERS (PALC:layer row nil))
      (PALC:layer "09_ESTIMATED_DIMS" nil)
      (setq name (strcat "PALC_CLEAN_" (itoa (getvar "MILLISECS"))) count 0)
      (while (tblsearch "BLOCK" name)
        (setq count (1+ count) name (strcat name "_" (itoa count))))
      (PALC:build name)
      (setq entity
        (entmakex
          (list '(0 . "INSERT") '(100 . "AcDbEntity") '(8 . "PALC_01_STRUCTURE")
                '(62 . 7) '(420 . 0) '(370 . 18) '(100 . "AcDbBlockReference")
                (cons 2 name) (cons 10 base) (cons 41 factor) (cons 42 factor)
                (cons 43 factor) '(50 . 0.0))))
      (if (null entity) (progn (princ "\nUnable to insert facade block.") (quit)))
      (setq PALC:LAST (list entity base factor nil))
      (setvar "INSUNITS" 4) (setvar "LWDISPLAY" 1) (setvar "FILLMODE" 1)
      (initget "Yes No")
      (setq dims (getkword "\nAdd estimated overall dimensions? [Yes/No] <Yes>: "))
      (if (not (equal dims "No")) (setq PALC:LAST (PALC:dimensions PALC:LAST)))
      (vla-Regen doc 1)
      (vl-catch-all-apply 'vla-ZoomWindow
        (list acad
          (vlax-3d-point (PALC:point '(-2000.0 -1200.0) base factor))
          (vlax-3d-point (PALC:point '(16000.0 12410.687) base factor))))
      (vla-EndUndoMark doc) (setq mark nil)
      (princ (strcat "\nFacade complete. Estimated width: " (rtos width 2 0)
                     " mm; estimated height: " (rtos (* factor 10610.687) 2 0)
                     " mm. One UNDO removes this insertion and its dimensions."))))
  (princ))

(defun c:PALACEDIMS (/ *error* doc mark)
  (setq doc (vla-get-ActiveDocument (vlax-get-acad-object)) mark nil)
  (defun *error* (message)
    (if mark (vl-catch-all-apply 'vla-EndUndoMark (list doc)))
    (princ (strcat "\nDimension command stopped: " message)) (princ))
  (if (and PALC:LAST (entget (car PALC:LAST)))
    (progn (vla-StartUndoMark doc) (setq mark T)
      (setq PALC:LAST (PALC:dimensions PALC:LAST))
      (vla-Regen doc 1) (vla-EndUndoMark doc) (setq mark nil)
      (princ "\nEstimated dimensions updated for the last facade insertion."))
    (princ "\nRun PALACE first."))
  (princ))

(defun c:PALACEINFO ()
  (princ "\nPALACE = draw self-contained facade; PALACEDIMS = native overall dimensions.")
  (princ "\nUnits are mm. Default estimated width 14000 mm; height 10610.687 mm.")
  (princ "\nBlack outlines 0.18 mm. Shared edges once, no loose ends; intentional joints remain.")
  (princ "\nThe reference is visually reconstructed; dimensions are estimated, not surveyed.")
  (princ))

(setq PALC:LAST nil)
(setq PALC:LAYERS
  '("01_STRUCTURE" "02_CORNICES" "03_FRAMES_DOORS" "04_GLAZING_SHUTTERS"
    "05_STONE_JOINTS" "06_ORNAMENT" "07_RAILINGS" "08_STEPS"))

(defun c:PALACESIZES (/ factor row width height)
  (setq factor (if PALC:LAST (caddr PALC:LAST) 1.0))
  (princ "\nEstimated dimensions in mm, scaled for the last insertion:")
  (foreach row PALC:SIZES
    (setq width (cadr row) height (caddr row))
    (princ (strcat "\n" (car row)
      (if width (strcat " | width=" (rtos (* factor width) 2 0)) "")
      (if height (strcat " | height/level=" (rtos (* factor height) 2 0)) ""))))
  (princ))

(setq PALC:DIMS
  '(
    ((0.0 10610.687) (14000.0 8076.3359) (7000.0 11610.687) 0.000000000000000)
    ((-381.6794 0.0) (0.0 10610.687) (-1300.0 5305.3435) 1.570796326794897)
  ))

; Each row: (layer closed-flag ((x y) ...)), in nominal estimated millimetres.
(setq PALC:DATA
  '(
    ; P0001 -- see feature_dimensions_mm.csv
    ("01_STRUCTURE" 0 (
      (183.2061 9572.5191) (183.2061 9587.7863) (4992.3664 9587.7863)
    ))
    ; P0002 -- see feature_dimensions_mm.csv
    ("01_STRUCTURE" 0 (
      (183.2061 9145.0382) (183.2061 8931.2977) (183.2061 8717.5573) (183.2061 8503.8168) (183.2061 8290.0763)
      (183.2061 8076.3359) (183.2061 7862.5954) (183.2061 7648.855) (183.2061 7435.1145) (183.2061 7221.374)
      (183.2061 7007.6336)
    ))
    ; P0003 -- see feature_dimensions_mm.csv
    ("01_STRUCTURE" 0 (
      (183.2061 5725.1908) (183.2061 5511.4504) (183.2061 5404.5802) (183.2061 5297.7099)
    ))
    ; P0004 -- see feature_dimensions_mm.csv
    ("01_STRUCTURE" 0 (
      (183.2061 4229.0076) (183.2061 4015.2672) (183.2061 3801.5267) (183.2061 3694.6565) (183.2061 3587.7863)
      (183.2061 3374.0458) (183.2061 3160.3053) (183.2061 2946.5649) (183.2061 2732.8244) (183.2061 2519.084)
    ))
    ; P0005 -- see feature_dimensions_mm.csv
    ("01_STRUCTURE" 0 (
      (793.8931 8076.3359) (1021.5267 8076.3359) (1171.7557 8076.3359) (1207.771 8076.3359) (1435.4046 8076.3359)
      (1621.6489 8076.3359) (1736.6412 8076.3359) (1849.2824 8076.3359) (2035.5267 8076.3359) (2047.3282 8076.3359)
      (2263.1603 8076.3359) (2358.0153 8076.3359) (2449.4046 8076.3359) (2677.0382 8076.3359) (2863.2824 8076.3359)
      (3064.1221 8076.3359) (3090.916 8076.3359) (3277.1603 8076.3359) (3504.7939 8076.3359) (3629.0076 8076.3359)
      (3691.0382 8076.3359) (3918.6718 8076.3359) (3939.6947 8076.3359) (4104.916 8076.3359) (4332.5496 8076.3359)
      (4518.7939 8076.3359) (4645.8015 8076.3359)
    ))
    ; P0006 -- see feature_dimensions_mm.csv
    ("01_STRUCTURE" 0 (
      (793.8931 3419.8473) (793.8931 3374.0458) (793.8931 3267.1756) (889.313 3267.1756) (961.8321 3267.1756)
      (961.8321 3160.3053) (961.8321 2961.8321) (961.8321 2946.5649) (961.8321 2839.6947) (961.8321 2732.8244)
      (961.8321 2641.2214) (961.8321 2519.084)
    ))
    ; P0007 -- see feature_dimensions_mm.csv
    ("01_STRUCTURE" 0 (
      (917.5573 809.1603) (961.8321 809.1603)
    ))
    ; P0008 -- see feature_dimensions_mm.csv
    ("01_STRUCTURE" 0 (
      (961.8321 7526.7176) (961.8321 7435.1145) (961.8321 7221.374) (961.8321 7114.5038) (961.8321 7007.6336)
      (961.8321 6992.3664) (961.8321 6977.0992) (961.8321 6793.8931) (961.8321 6656.4885) (961.8321 6580.1527)
      (961.8321 6564.8855) (961.8321 6366.4122) (961.8321 6259.542) (961.8321 6152.6718) (961.8321 5969.4656)
      (961.8321 5938.9313) (961.8321 5816.7939) (961.8321 5725.1908) (961.8321 5511.4504) (961.8321 5465.6489)
      (961.8321 5297.7099)
    ))
    ; P0009 -- see feature_dimensions_mm.csv
    ("01_STRUCTURE" 0 (
      (961.8321 3740.458) (961.8321 3801.5267) (961.8321 4015.2672) (961.8321 4229.0076) (961.8321 4442.7481)
      (961.8321 4549.6183)
    ))
    ; P0010 -- see feature_dimensions_mm.csv
    ("01_STRUCTURE" 0 (
      (1358.7786 5816.7939) (1358.7786 5465.6489) (1358.7786 3740.458) (961.8321 3740.458)
    ))
    ; P0011 -- see feature_dimensions_mm.csv
    ("01_STRUCTURE" 0 (
      (961.8321 3664.1221) (961.8321 3679.3893) (961.8321 3740.458)
    ))
    ; P0012 -- see feature_dimensions_mm.csv
    ("01_STRUCTURE" 0 (
      (961.8321 3664.1221) (1358.7786 3664.1221) (1358.7786 3633.5878)
    ))
    ; P0013 -- see feature_dimensions_mm.csv
    ("01_STRUCTURE" 0 (
      (961.8321 3664.1221) (961.8321 3633.5878)
    ))
    ; P0014 -- see feature_dimensions_mm.csv
    ("01_STRUCTURE" 0 (
      (961.8321 1984.7328) (961.8321 1877.8626) (961.8321 1664.1221) (961.8321 1633.5878) (961.8321 1450.3817)
      (961.8321 1282.4427) (961.8321 1236.6412) (961.8321 1129.771) (961.8321 1022.9008) (961.8321 931.2977)
      (961.8321 809.1603)
    ))
    ; P0015 -- see feature_dimensions_mm.csv
    ("01_STRUCTURE" 0 (
      (961.8321 809.1603) (961.8321 656.4885) (1435.1145 656.4885)
    ))
    ; P0016 -- see feature_dimensions_mm.csv
    ("01_STRUCTURE" 0 (
      (1435.1145 1862.5954) (1435.1145 1633.5878) (1435.1145 1282.4427) (1435.1145 931.2977)
    ))
    ; P0017 -- see feature_dimensions_mm.csv
    ("01_STRUCTURE" 0 (
      (2868.916 1906.2443) (2865.0076 1943.6336) (2858.4885 1980.687)
    ))
    ; P0018 -- see feature_dimensions_mm.csv
    ("01_STRUCTURE" 0 (
      (2946.5649 1862.5954) (2870.229 1862.5954) (2870.229 1868.7023)
    ))
    ; P0019 -- see feature_dimensions_mm.csv
    ("01_STRUCTURE" 0 (
      (3114.5038 1969.4656) (3114.5038 1862.5954) (3129.771 1862.5954)
    ))
    ; P0020 -- see feature_dimensions_mm.csv
    ("01_STRUCTURE" 0 (
      (3129.771 656.4885) (3221.374 656.4885)
    ))
    ; P0021 -- see feature_dimensions_mm.csv
    ("01_STRUCTURE" 0 (
      (3221.374 1984.7328) (3221.374 1633.5878)
    ))
    ; P0022 -- see feature_dimensions_mm.csv
    ("01_STRUCTURE" 0 (
      (4104.6565 2233.1145) (4090.2901 2259.542) (4074.1985 2284.9924)
    ))
    ; P0023 -- see feature_dimensions_mm.csv
    ("01_STRUCTURE" 0 (
      (4152.6718 931.2977) (4152.6718 1282.4427) (4152.6718 1633.5878) (4152.6718 1984.7328) (4152.6718 2030.5344)
      (4151.6794 2060.4885) (4148.687 2090.3206) (4143.7252 2119.8931) (4136.8092 2149.084) (4127.9542 2177.7557)
      (4117.2214 2205.8015)
    ))
    ; P0024 -- see feature_dimensions_mm.csv
    ("01_STRUCTURE" 0 (
      (4290.0763 1969.4656) (4351.145 1862.5954) (4244.2748 1862.5954) (4244.2748 1633.5878) (4244.2748 1282.4427)
      (4244.2748 931.2977) (4244.2748 656.4885) (4152.6718 656.4885)
    ))
    ; P0025 -- see feature_dimensions_mm.csv
    ("01_STRUCTURE" 0 (
      (4183.2061 2061.0687) (4732.8244 2061.0687)
    ))
    ; P0026 -- see feature_dimensions_mm.csv
    ("01_STRUCTURE" 0 (
      (4992.3664 3740.458) (4595.4198 3740.458) (4595.4198 5465.6489) (4595.4198 5816.7939) (4595.4198 5969.4656)
      (4595.4198 6015.2672) (4351.145 6015.2672) (4351.145 6244.2748)
    ))
    ; P0027 -- see feature_dimensions_mm.csv
    ("01_STRUCTURE" 0 (
      (4519.084 931.2977) (4519.084 1282.4427) (4519.084 1633.5878) (4519.084 1862.5954) (4656.4885 1862.5954)
      (4656.4885 1969.4656)
    ))
    ; P0028 -- see feature_dimensions_mm.csv
    ("01_STRUCTURE" 0 (
      (4595.4198 3664.1221) (4992.3664 3664.1221) (4992.3664 3633.5878)
    ))
    ; P0029 -- see feature_dimensions_mm.csv
    ("01_STRUCTURE" 0 (
      (4645.8015 8122.1374) (4641.2214 8122.1374)
    ))
    ; P0030 -- see feature_dimensions_mm.csv
    ("01_STRUCTURE" 0 (
      (4783.2061 5465.6489) (4854.9618 5465.6489) (4874.8092 5465.6489) (4946.5649 5465.6489) (4966.4122 5465.6489)
      (4992.3664 5465.6489) (4992.3664 5816.7939)
    ))
    ; P0031 -- see feature_dimensions_mm.csv
    ("01_STRUCTURE" 0 (
      (4992.3664 7358.7786) (4992.3664 7312.9771) (4992.3664 6992.3664) (4992.3664 6977.0992)
    ))
    ; P0032 -- see feature_dimensions_mm.csv
    ("01_STRUCTURE" 0 (
      (4992.3664 4717.5573) (4992.3664 4091.6031)
    ))
    ; P0033 -- see feature_dimensions_mm.csv
    ("01_STRUCTURE" 0 (
      (5175.5725 3465.6489) (5175.5725 3267.1756) (4992.3664 3267.1756) (4992.3664 2961.8321) (4992.3664 2839.6947)
      (4992.3664 2641.2214) (4992.3664 2305.3435) (4992.3664 2213.7405)
    ))
    ; P0034 -- see feature_dimensions_mm.csv
    ("01_STRUCTURE" 0 (
      (4992.3664 793.8931) (8473.2824 793.8931)
    ))
    ; P0035 -- see feature_dimensions_mm.csv
    ("01_STRUCTURE" 0 (
      (5221.374 2213.7405) (5221.374 2839.6947) (5221.374 3465.6489)
    ))
    ; P0036 -- see feature_dimensions_mm.csv
    ("01_STRUCTURE" 0 (
      (6122.1374 3465.6489) (6122.1374 2839.6947) (6122.1374 2213.7405) (6122.1374 1587.7863) (6122.1374 1099.2366)
      (6122.1374 1053.4351) (6096.687 1053.4351) (5246.8244 1053.4351) (5221.374 1053.4351) (5221.374 1099.2366)
      (5221.374 1587.7863)
    ))
    ; P0037 -- see feature_dimensions_mm.csv
    ("01_STRUCTURE" 0 (
      (7480.916 1587.7863) (7480.916 1099.2366) (7480.916 1053.4351) (7455.4656 1053.4351) (6284.9924 1053.4351)
      (6259.542 1053.4351) (6259.542 1099.2366) (6259.542 1587.7863) (6259.542 2213.7405) (6259.542 2839.6947)
      (6259.542 3465.6489)
    ))
    ; P0038 -- see feature_dimensions_mm.csv
    ("01_STRUCTURE" 0 (
      (7480.916 3465.6489) (7480.916 2839.6947) (7480.916 2213.7405)
    ))
    ; P0039 -- see feature_dimensions_mm.csv
    ("01_STRUCTURE" 0 (
      (8473.2824 3618.3206) (8519.084 3618.3206)
    ))
    ; P0040 -- see feature_dimensions_mm.csv
    ("01_STRUCTURE" 0 (
      (8473.2824 793.8931) (8473.2824 961.8321) (8473.2824 1016.7939)
    ))
    ; P0041 -- see feature_dimensions_mm.csv
    ("01_STRUCTURE" 0 (
      (8473.2824 793.8931) (8473.2824 290.0763) (8519.084 290.0763) (10412.2137 290.0763) (10519.084 290.0763)
      (10519.084 656.4885)
    ))
    ; P0042 -- see feature_dimensions_mm.csv
    ("01_STRUCTURE" 0 (
      (10290.0763 7541.9847) (10122.1374 7541.9847) (10122.1374 7740.458) (10122.1374 7923.6641) (8671.7557 7923.6641)
    ))
    ; P0043 -- see feature_dimensions_mm.csv
    ("01_STRUCTURE" 0 (
      (8671.7557 4717.5573) (8671.7557 5343.5115) (8671.7557 5969.4656) (8671.7557 6473.2824) (8671.7557 6625.9542)
      (8671.7557 6961.8321) (8671.7557 7312.9771) (8671.7557 7358.7786) (8671.7557 7374.0458)
    ))
    ; P0044 -- see feature_dimensions_mm.csv
    ("01_STRUCTURE" 0 (
      (8687.0229 3618.3206) (8671.7557 3618.3206) (8671.7557 4091.6031)
    ))
    ; P0045 -- see feature_dimensions_mm.csv
    ("01_STRUCTURE" 0 (
      (10274.8092 3618.3206) (8687.0229 3618.3206)
    ))
    ; P0046 -- see feature_dimensions_mm.csv
    ("01_STRUCTURE" 0 (
      (8687.0229 3618.3206) (8687.0229 4473.2824) (8793.8931 4473.2824)
    ))
    ; P0047 -- see feature_dimensions_mm.csv
    ("01_STRUCTURE" 0 (
      (8793.8931 4412.2137) (8778.626 4412.2137) (8748.0916 4412.2137) (8748.0916 3832.0611) (8778.626 3832.0611)
      (8793.8931 3832.0611)
    ))
    ; P0048 -- see feature_dimensions_mm.csv
    ("01_STRUCTURE" 0 (
      (8803.8473 5405.0076) (8815.771 5426.7328)
    ))
    ; P0049 -- see feature_dimensions_mm.csv
    ("01_STRUCTURE" 0 (
      (8851.7252 5467.4351) (8875.084 5486.4275) (8901.542 5504.5038) (8930.7634 5521.6947) (8962.3969 5538.0)
      (8996.1069 5553.4046) (9031.5115 5567.9389) (9068.2901 5581.6031) (9106.0611 5594.3969) (9144.5191 5606.3206)
      (9183.2824 5617.3893)
    ))
    ; P0050 -- see feature_dimensions_mm.csv
    ("01_STRUCTURE" 0 (
      (9369.5573 5660.0916) (9402.855 5666.1374) (9434.0153 5671.374)
    ))
    ; P0051 -- see feature_dimensions_mm.csv
    ("01_STRUCTURE" 0 (
      (9488.5496 5679.3893) (9514.3969 5675.7863) (9543.084 5671.374) (9574.2443 5666.1374) (9607.542 5660.0916)
      (9642.626 5653.2214) (9679.145 5645.5267) (9716.7481 5636.9924) (9755.0992 5627.6183) (9793.8168 5617.3893)
      (9832.5802 5606.3206) (9871.0382 5594.3969) (9908.8244 5581.6031) (9945.5878 5567.9389) (9981.0076 5553.4046)
      (10014.7023 5538.0) (10046.3359 5521.6947) (10075.5573 5504.5038) (10102.0153 5486.4275) (10125.374 5467.4351)
    ))
    ; P0052 -- see feature_dimensions_mm.csv
    ("01_STRUCTURE" 0 (
      (9584.1221 2381.6794) (9408.2443 2381.6794) (9383.9389 2509.2519) (9358.7786 2641.2214) (9633.5878 2641.2214)
      (9608.4427 2509.2519)
    ))
    ; P0053 -- see feature_dimensions_mm.csv
    ("01_STRUCTURE" 0 (
      (10183.2061 4473.2824) (10290.0763 4473.2824) (10290.0763 5465.6489) (10290.0763 5816.7939) (10290.0763 5969.4656)
      (10290.0763 6564.8855) (10290.0763 6656.4885) (10290.0763 6977.0992) (10290.0763 6992.3664) (10290.0763 7526.7176)
    ))
    ; P0054 -- see feature_dimensions_mm.csv
    ("01_STRUCTURE" 0 (
      (10183.2061 4412.2137) (10183.2061 3832.0611) (10198.4733 3832.0611) (10229.0076 3832.0611) (10229.0076 4412.2137)
      (10198.4733 4412.2137)
    ))
    ; P0055 -- see feature_dimensions_mm.csv
    ("01_STRUCTURE" 0 (
      (10687.0229 3664.1221) (10335.8779 3664.1221) (10290.0763 3664.1221)
    ))
    ; P0056 -- see feature_dimensions_mm.csv
    ("01_STRUCTURE" 0 (
      (10519.084 2305.3435) (10519.084 2641.2214) (10519.084 2961.8321) (10519.084 3267.1756) (10519.084 3282.4427)
    ))
    ; P0057 -- see feature_dimensions_mm.csv
    ("01_STRUCTURE" 0 (
      (10519.084 656.4885) (10519.084 931.2977) (10519.084 1282.4427) (10519.084 1633.5878) (10519.084 1984.7328)
      (10519.084 2008.7176) (10519.084 2061.0687)
    ))
    ; P0058 -- see feature_dimensions_mm.csv
    ("01_STRUCTURE" 0 (
      (10580.1527 1282.4427) (10580.1527 931.2977) (10580.1527 656.4885) (10519.084 656.4885)
    ))
    ; P0059 -- see feature_dimensions_mm.csv
    ("01_STRUCTURE" 0 (
      (13435.1145 5969.4656) (13435.1145 6015.2672) (13190.8397 6015.2672) (13190.8397 6244.2748) (10931.2977 6244.2748)
      (10931.2977 6015.2672) (10687.0229 6015.2672) (10687.0229 5969.4656) (10687.0229 5816.7939)
    ))
    ; P0060 -- see feature_dimensions_mm.csv
    ("01_STRUCTURE" 0 (
      (10687.0229 5465.6489) (10687.0229 5389.313)
    ))
    ; P0061 -- see feature_dimensions_mm.csv
    ("01_STRUCTURE" 0 (
      (11053.4351 2365.8473) (11019.4962 2346.0)
    ))
    ; P0062 -- see feature_dimensions_mm.csv
    ("01_STRUCTURE" 0 (
      (11249.4351 2433.2366) (11239.6336 2431.7252) (11200.7176 2423.1908) (11162.4733 2412.2901) (11125.084 2399.0534)
      (11088.6718 2383.542)
    ))
    ; P0063 -- see feature_dimensions_mm.csv
    ("01_STRUCTURE" 0 (
      (11477.9237 2431.7252) (11468.1221 2433.2366)
    ))
    ; P0064 -- see feature_dimensions_mm.csv
    ("01_STRUCTURE" 0 (
      (11664.1221 2365.8473) (11628.8855 2383.542) (11592.4733 2399.0534) (11555.084 2412.2901) (11516.8397 2423.1908)
    ))
    ; P0065 -- see feature_dimensions_mm.csv
    ("01_STRUCTURE" 0 (
      (11730.5344 2324.1221) (11698.0611 2346.0)
    ))
    ; P0066 -- see feature_dimensions_mm.csv
    ("01_STRUCTURE" 0 (
      (11968.1527 1906.2443) (11964.2443 1943.6336) (11963.5267 1947.6947) (12000.0 1862.5954)
    ))
    ; P0067 -- see feature_dimensions_mm.csv
    ("01_STRUCTURE" 0 (
      (11969.4656 1862.5954) (11969.4656 1868.7023)
    ))
    ; P0068 -- see feature_dimensions_mm.csv
    ("01_STRUCTURE" 0 (
      (13300.2443 1984.7328) (13293.3588 2012.4427)
    ))
    ; P0069 -- see feature_dimensions_mm.csv
    ("01_STRUCTURE" 0 (
      (13435.1145 5465.6489) (13832.0611 5465.6489)
    ))
    ; P0070 -- see feature_dimensions_mm.csv
    ("01_STRUCTURE" 0 (
      (13832.0611 3633.5878) (13832.0611 3664.1221) (13435.1145 3664.1221) (13435.1145 3633.5878)
    ))
    ; P0071 -- see feature_dimensions_mm.csv
    ("01_STRUCTURE" 0 (
      (13832.0611 5465.6489) (13832.0611 5969.4656) (13832.0611 6564.8855)
    ))
    ; P0072 -- see feature_dimensions_mm.csv
    ("01_STRUCTURE" 0 (
      (13832.0611 5465.6489) (13832.0611 3740.458)
    ))
    ; P0073 -- see feature_dimensions_mm.csv
    ("01_STRUCTURE" 1 (
      (1938.9313 3099.2366) (2061.0687 3099.2366) (2061.0687 2961.8321) (2061.0687 2809.1603) (1938.9313 2809.1603)
      (1938.9313 2961.8321)
    ))
    ; P0074 -- see feature_dimensions_mm.csv
    ("01_STRUCTURE" 1 (
      (2229.0076 3099.2366) (2351.145 3099.2366) (2351.145 2961.8321) (2351.145 2809.1603) (2229.0076 2809.1603)
      (2229.0076 2961.8321)
    ))
    ; P0075 -- see feature_dimensions_mm.csv
    ("01_STRUCTURE" 1 (
      (2519.084 3099.2366) (2641.2214 3099.2366) (2641.2214 2961.8321) (2641.2214 2809.1603) (2519.084 2809.1603)
      (2519.084 2961.8321)
    ))
    ; P0076 -- see feature_dimensions_mm.csv
    ("01_STRUCTURE" 1 (
      (3343.5115 3099.2366) (3465.6489 3099.2366) (3465.6489 2961.8321) (3465.6489 2809.1603) (3343.5115 2809.1603)
      (3343.5115 2961.8321)
    ))
    ; P0077 -- see feature_dimensions_mm.csv
    ("01_STRUCTURE" 1 (
      (3633.5878 3099.2366) (3755.7252 3099.2366) (3755.7252 2961.8321) (3755.7252 2809.1603) (3633.5878 2809.1603)
      (3633.5878 2961.8321)
    ))
    ; P0078 -- see feature_dimensions_mm.csv
    ("01_STRUCTURE" 1 (
      (3923.6641 3099.2366) (4045.8015 3099.2366) (4045.8015 2961.8321) (4045.8015 2809.1603) (3923.6641 2809.1603)
      (3923.6641 2961.8321)
    ))
    ; P0079 -- see feature_dimensions_mm.csv
    ("02_CORNICES" 0 (
      (5160.3053 10259.542) (0.0 10259.542)
    ))
    ; P0080 -- see feature_dimensions_mm.csv
    ("02_CORNICES" 0 (
      (122.1374 10122.1374) (106.8702 10122.1374) (0.0 10259.542)
    ))
    ; P0081 -- see feature_dimensions_mm.csv
    ("02_CORNICES" 0 (
      (0.0 10259.542) (0.0 10610.687) (245.7252 10610.687) (272.5344 10525.1908) (299.3435 10525.1908)
      (321.6794 10396.9466) (379.7557 10396.9466) (402.1069 10525.1908) (424.4427 10525.1908) (446.7786 10610.687)
      (692.5038 10610.687) (719.313 10525.1908) (746.1221 10525.1908) (768.458 10396.9466) (826.5496 10396.9466)
      (848.8855 10525.1908) (871.2214 10525.1908) (893.5573 10610.687) (1139.2824 10610.687) (1166.0916 10525.1908)
      (1192.9008 10525.1908) (1215.2366 10396.9466) (1273.3282 10396.9466) (1295.6641 10525.1908) (1318.0 10525.1908)
      (1340.3359 10610.687) (1586.0611 10610.687) (1612.8702 10525.1908) (1639.6794 10525.1908) (1662.0153 10396.9466)
      (1720.1069 10396.9466) (1742.4427 10525.1908) (1764.7786 10525.1908) (1787.1145 10610.687) (2032.855 10610.687)
      (2059.6489 10525.1908) (2086.458 10525.1908) (2108.7939 10396.9466) (2166.8855 10396.9466) (2189.2214 10525.1908)
      (2211.5573 10525.1908) (2233.8931 10610.687) (2479.6336 10610.687) (2506.4275 10525.1908) (2533.2366 10525.1908)
      (2555.5725 10396.9466) (2613.6641 10396.9466) (2636.0 10525.1908) (2658.3359 10525.1908) (2680.6718 10610.687)
      (2926.4122 10610.687) (2953.2214 10525.1908) (2980.0153 10525.1908) (3002.3664 10396.9466) (3060.4427 10396.9466)
      (3082.7786 10525.1908) (3105.1145 10525.1908) (3127.4504 10610.687) (3373.1908 10610.687) (3400.0 10525.1908)
      (3426.7939 10525.1908) (3449.145 10396.9466) (3507.2214 10396.9466) (3529.5573 10525.1908) (3551.8931 10525.1908)
      (3574.2443 10610.687) (3819.9695 10610.687) (3846.7786 10525.1908) (3873.5725 10525.1908) (3895.9237 10396.9466)
      (3954.0 10396.9466) (3976.3359 10525.1908) (3998.6718 10525.1908) (4021.0229 10610.687) (4266.7481 10610.687)
      (4293.5573 10525.1908) (4320.3664 10525.1908) (4342.7023 10396.9466) (4400.7786 10396.9466) (4423.1145 10525.1908)
      (4445.4504 10525.1908) (4467.8015 10610.687) (4713.5267 10610.687) (4740.3359 10525.1908) (4767.145 10525.1908)
      (4789.4809 10396.9466) (4847.5573 10396.9466) (4869.8931 10525.1908) (4892.2443 10525.1908) (4914.5802 10610.687)
      (5160.3053 10610.687) (5160.3053 10259.542)
    ))
    ; P0082 -- see feature_dimensions_mm.csv
    ("02_CORNICES" 0 (
      (5007.6336 10122.1374) (122.1374 10122.1374)
    ))
    ; P0083 -- see feature_dimensions_mm.csv
    ("02_CORNICES" 0 (
      (167.9389 9969.4656) (122.1374 9969.4656) (122.1374 10122.1374)
    ))
    ; P0084 -- see feature_dimensions_mm.csv
    ("02_CORNICES" 0 (
      (5007.6336 9969.4656) (167.9389 9969.4656)
    ))
    ; P0085 -- see feature_dimensions_mm.csv
    ("02_CORNICES" 0 (
      (183.2061 9923.6641) (167.9389 9923.6641) (167.9389 9969.4656)
    ))
    ; P0086 -- see feature_dimensions_mm.csv
    ("02_CORNICES" 0 (
      (167.9389 9969.4656) (167.9389 9984.7328) (5007.6336 9984.7328)
    ))
    ; P0087 -- see feature_dimensions_mm.csv
    ("02_CORNICES" 0 (
      (267.5725 9923.6641) (183.2061 9923.6641)
    ))
    ; P0088 -- see feature_dimensions_mm.csv
    ("02_CORNICES" 0 (
      (183.2061 9603.0534) (183.2061 9923.6641)
    ))
    ; P0089 -- see feature_dimensions_mm.csv
    ("02_CORNICES" 0 (
      (183.2061 9923.6641) (183.2061 9938.9313) (267.5725 9938.9313)
    ))
    ; P0090 -- see feature_dimensions_mm.csv
    ("02_CORNICES" 0 (
      (267.5725 9603.0534) (183.2061 9603.0534)
    ))
    ; P0091 -- see feature_dimensions_mm.csv
    ("02_CORNICES" 0 (
      (183.2061 9587.7863) (183.2061 9603.0534)
    ))
    ; P0092 -- see feature_dimensions_mm.csv
    ("02_CORNICES" 0 (
      (4992.3664 9557.2519) (4900.0 9557.2519) (4335.1145 9557.2519) (3629.0076 9557.2519) (3064.1221 9557.2519)
      (2358.0153 9557.2519) (2047.3282 9557.2519) (1736.6412 9557.2519) (1171.7557 9557.2519) (606.8702 9557.2519)
      (183.2061 9557.2519)
    ))
    ; P0093 -- see feature_dimensions_mm.csv
    ("02_CORNICES" 0 (
      (267.5725 9938.9313) (351.9542 9938.9313)
    ))
    ; P0094 -- see feature_dimensions_mm.csv
    ("02_CORNICES" 0 (
      (267.5725 9938.9313) (267.5725 9923.6641)
    ))
    ; P0095 -- see feature_dimensions_mm.csv
    ("02_CORNICES" 0 (
      (351.9542 9923.6641) (267.5725 9923.6641)
    ))
    ; P0096 -- see feature_dimensions_mm.csv
    ("02_CORNICES" 0 (
      (267.5725 9923.6641) (267.5725 9603.0534)
    ))
    ; P0097 -- see feature_dimensions_mm.csv
    ("02_CORNICES" 0 (
      (351.9542 9603.0534) (267.5725 9603.0534)
    ))
    ; P0098 -- see feature_dimensions_mm.csv
    ("02_CORNICES" 0 (
      (351.9542 9938.9313) (436.3206 9938.9313)
    ))
    ; P0099 -- see feature_dimensions_mm.csv
    ("02_CORNICES" 0 (
      (351.9542 9938.9313) (351.9542 9923.6641)
    ))
    ; P0100 -- see feature_dimensions_mm.csv
    ("02_CORNICES" 0 (
      (436.3206 9923.6641) (351.9542 9923.6641)
    ))
    ; P0101 -- see feature_dimensions_mm.csv
    ("02_CORNICES" 0 (
      (351.9542 9923.6641) (351.9542 9603.0534)
    ))
    ; P0102 -- see feature_dimensions_mm.csv
    ("02_CORNICES" 0 (
      (436.3206 9603.0534) (351.9542 9603.0534)
    ))
    ; P0103 -- see feature_dimensions_mm.csv
    ("02_CORNICES" 0 (
      (436.3206 9938.9313) (520.687 9938.9313)
    ))
    ; P0104 -- see feature_dimensions_mm.csv
    ("02_CORNICES" 0 (
      (436.3206 9938.9313) (436.3206 9923.6641)
    ))
    ; P0105 -- see feature_dimensions_mm.csv
    ("02_CORNICES" 0 (
      (520.687 9923.6641) (436.3206 9923.6641)
    ))
    ; P0106 -- see feature_dimensions_mm.csv
    ("02_CORNICES" 0 (
      (436.3206 9923.6641) (436.3206 9603.0534)
    ))
    ; P0107 -- see feature_dimensions_mm.csv
    ("02_CORNICES" 0 (
      (520.687 9603.0534) (436.3206 9603.0534)
    ))
    ; P0108 -- see feature_dimensions_mm.csv
    ("02_CORNICES" 0 (
      (520.687 9938.9313) (605.0687 9938.9313)
    ))
    ; P0109 -- see feature_dimensions_mm.csv
    ("02_CORNICES" 0 (
      (520.687 9938.9313) (520.687 9923.6641)
    ))
    ; P0110 -- see feature_dimensions_mm.csv
    ("02_CORNICES" 0 (
      (605.0687 9923.6641) (520.687 9923.6641)
    ))
    ; P0111 -- see feature_dimensions_mm.csv
    ("02_CORNICES" 0 (
      (520.687 9923.6641) (520.687 9603.0534)
    ))
    ; P0112 -- see feature_dimensions_mm.csv
    ("02_CORNICES" 0 (
      (605.0687 9603.0534) (520.687 9603.0534)
    ))
    ; P0113 -- see feature_dimensions_mm.csv
    ("02_CORNICES" 0 (
      (605.0687 9938.9313) (689.4351 9938.9313)
    ))
    ; P0114 -- see feature_dimensions_mm.csv
    ("02_CORNICES" 0 (
      (605.0687 9938.9313) (605.0687 9923.6641)
    ))
    ; P0115 -- see feature_dimensions_mm.csv
    ("02_CORNICES" 0 (
      (689.4351 9923.6641) (605.0687 9923.6641)
    ))
    ; P0116 -- see feature_dimensions_mm.csv
    ("02_CORNICES" 0 (
      (605.0687 9923.6641) (605.0687 9603.0534)
    ))
    ; P0117 -- see feature_dimensions_mm.csv
    ("02_CORNICES" 0 (
      (689.4351 9603.0534) (605.0687 9603.0534)
    ))
    ; P0118 -- see feature_dimensions_mm.csv
    ("02_CORNICES" 0 (
      (689.4351 9938.9313) (773.8015 9938.9313)
    ))
    ; P0119 -- see feature_dimensions_mm.csv
    ("02_CORNICES" 0 (
      (689.4351 9938.9313) (689.4351 9923.6641)
    ))
    ; P0120 -- see feature_dimensions_mm.csv
    ("02_CORNICES" 0 (
      (773.8015 9923.6641) (689.4351 9923.6641)
    ))
    ; P0121 -- see feature_dimensions_mm.csv
    ("02_CORNICES" 0 (
      (689.4351 9923.6641) (689.4351 9603.0534)
    ))
    ; P0122 -- see feature_dimensions_mm.csv
    ("02_CORNICES" 0 (
      (773.8015 9603.0534) (689.4351 9603.0534)
    ))
    ; P0123 -- see feature_dimensions_mm.csv
    ("02_CORNICES" 0 (
      (773.8015 9938.9313) (858.1832 9938.9313)
    ))
    ; P0124 -- see feature_dimensions_mm.csv
    ("02_CORNICES" 0 (
      (773.8015 9938.9313) (773.8015 9923.6641)
    ))
    ; P0125 -- see feature_dimensions_mm.csv
    ("02_CORNICES" 0 (
      (858.1832 9923.6641) (773.8015 9923.6641)
    ))
    ; P0126 -- see feature_dimensions_mm.csv
    ("02_CORNICES" 0 (
      (773.8015 9923.6641) (773.8015 9603.0534)
    ))
    ; P0127 -- see feature_dimensions_mm.csv
    ("02_CORNICES" 0 (
      (858.1832 9603.0534) (773.8015 9603.0534)
    ))
    ; P0128 -- see feature_dimensions_mm.csv
    ("02_CORNICES" 0 (
      (5137.4046 3389.313) (5068.7023 3297.7099) (885.4962 3297.7099) (824.4275 3379.1298)
    ))
    ; P0129 -- see feature_dimensions_mm.csv
    ("02_CORNICES" 0 (
      (5137.4046 3389.313) (5145.0382 3389.313) (5145.0382 3282.4427) (824.4275 3282.4427) (824.4275 3379.1298)
    ))
    ; P0130 -- see feature_dimensions_mm.csv
    ("02_CORNICES" 0 (
      (824.4275 3379.1298) (793.8931 3419.8473) (793.8931 3587.7863) (793.8931 3633.5878) (854.9618 3633.5878)
    ))
    ; P0131 -- see feature_dimensions_mm.csv
    ("02_CORNICES" 0 (
      (824.4275 3379.1298) (824.4275 3389.313) (5137.4046 3389.313)
    ))
    ; P0132 -- see feature_dimensions_mm.csv
    ("02_CORNICES" 0 (
      (854.9618 3633.5878) (931.2977 3633.5878)
    ))
    ; P0133 -- see feature_dimensions_mm.csv
    ("02_CORNICES" 0 (
      (5114.5038 3633.5878) (5114.5038 3618.3206) (854.9618 3618.3206) (854.9618 3633.5878)
    ))
    ; P0134 -- see feature_dimensions_mm.csv
    ("02_CORNICES" 0 (
      (854.9618 3633.5878) (854.9618 3679.3893) (931.2977 3679.3893)
    ))
    ; P0135 -- see feature_dimensions_mm.csv
    ("02_CORNICES" 0 (
      (858.1832 9938.9313) (942.5496 9938.9313)
    ))
    ; P0136 -- see feature_dimensions_mm.csv
    ("02_CORNICES" 0 (
      (858.1832 9938.9313) (858.1832 9923.6641)
    ))
    ; P0137 -- see feature_dimensions_mm.csv
    ("02_CORNICES" 0 (
      (942.5496 9923.6641) (858.1832 9923.6641)
    ))
    ; P0138 -- see feature_dimensions_mm.csv
    ("02_CORNICES" 0 (
      (858.1832 9923.6641) (858.1832 9603.0534)
    ))
    ; P0139 -- see feature_dimensions_mm.csv
    ("02_CORNICES" 0 (
      (942.5496 9603.0534) (858.1832 9603.0534)
    ))
    ; P0140 -- see feature_dimensions_mm.csv
    ("02_CORNICES" 0 (
      (931.2977 3679.3893) (961.8321 3679.3893) (1358.7786 3679.3893) (1389.313 3679.3893)
    ))
    ; P0141 -- see feature_dimensions_mm.csv
    ("02_CORNICES" 0 (
      (931.2977 3679.3893) (931.2977 3633.5878)
    ))
    ; P0142 -- see feature_dimensions_mm.csv
    ("02_CORNICES" 0 (
      (961.8321 3740.458) (931.2977 3740.458) (931.2977 3679.3893)
    ))
    ; P0143 -- see feature_dimensions_mm.csv
    ("02_CORNICES" 0 (
      (931.2977 3633.5878) (961.8321 3633.5878) (1358.7786 3633.5878) (1389.313 3633.5878)
    ))
    ; P0144 -- see feature_dimensions_mm.csv
    ("02_CORNICES" 0 (
      (942.5496 9938.9313) (1026.916 9938.9313)
    ))
    ; P0145 -- see feature_dimensions_mm.csv
    ("02_CORNICES" 0 (
      (942.5496 9938.9313) (942.5496 9923.6641)
    ))
    ; P0146 -- see feature_dimensions_mm.csv
    ("02_CORNICES" 0 (
      (1026.916 9923.6641) (942.5496 9923.6641)
    ))
    ; P0147 -- see feature_dimensions_mm.csv
    ("02_CORNICES" 0 (
      (942.5496 9923.6641) (942.5496 9603.0534)
    ))
    ; P0148 -- see feature_dimensions_mm.csv
    ("02_CORNICES" 0 (
      (1026.916 9603.0534) (942.5496 9603.0534)
    ))
    ; P0149 -- see feature_dimensions_mm.csv
    ("02_CORNICES" 0 (
      (1031.1756 6656.4885) (961.8321 6656.4885) (946.5649 6656.4885)
    ))
    ; P0150 -- see feature_dimensions_mm.csv
    ("02_CORNICES" 0 (
      (961.8321 6564.8855) (946.5649 6564.8855) (946.5649 6580.1527) (946.5649 6656.4885)
    ))
    ; P0151 -- see feature_dimensions_mm.csv
    ("02_CORNICES" 0 (
      (946.5649 6656.4885) (946.5649 6793.8931) (946.5649 6977.0992) (961.8321 6977.0992) (1031.1756 6977.0992)
    ))
    ; P0152 -- see feature_dimensions_mm.csv
    ("02_CORNICES" 0 (
      (1021.5267 8076.3359) (1046.3511 7996.9466) (1071.1908 7996.9466) (1091.8779 7877.8626) (1145.6947 7877.8626)
      (1166.3817 7996.9466) (1187.084 7996.9466) (1207.771 8076.3359)
    ))
    ; P0153 -- see feature_dimensions_mm.csv
    ("02_CORNICES" 0 (
      (1026.916 9938.9313) (1111.2824 9938.9313)
    ))
    ; P0154 -- see feature_dimensions_mm.csv
    ("02_CORNICES" 0 (
      (1026.916 9938.9313) (1026.916 9923.6641)
    ))
    ; P0155 -- see feature_dimensions_mm.csv
    ("02_CORNICES" 0 (
      (1111.2824 9923.6641) (1026.916 9923.6641)
    ))
    ; P0156 -- see feature_dimensions_mm.csv
    ("02_CORNICES" 0 (
      (1026.916 9923.6641) (1026.916 9603.0534)
    ))
    ; P0157 -- see feature_dimensions_mm.csv
    ("02_CORNICES" 0 (
      (1111.2824 9603.0534) (1026.916 9603.0534)
    ))
    ; P0158 -- see feature_dimensions_mm.csv
    ("02_CORNICES" 0 (
      (1031.1756 6977.0992) (1115.771 6977.0992)
    ))
    ; P0159 -- see feature_dimensions_mm.csv
    ("02_CORNICES" 0 (
      (1031.1756 6977.0992) (1031.1756 6656.4885)
    ))
    ; P0160 -- see feature_dimensions_mm.csv
    ("02_CORNICES" 0 (
      (1115.771 6656.4885) (1031.1756 6656.4885)
    ))
    ; P0161 -- see feature_dimensions_mm.csv
    ("02_CORNICES" 0 (
      (1111.2824 9938.9313) (1195.6641 9938.9313)
    ))
    ; P0162 -- see feature_dimensions_mm.csv
    ("02_CORNICES" 0 (
      (1111.2824 9938.9313) (1111.2824 9923.6641)
    ))
    ; P0163 -- see feature_dimensions_mm.csv
    ("02_CORNICES" 0 (
      (1195.6641 9923.6641) (1111.2824 9923.6641)
    ))
    ; P0164 -- see feature_dimensions_mm.csv
    ("02_CORNICES" 0 (
      (1111.2824 9923.6641) (1111.2824 9603.0534)
    ))
    ; P0165 -- see feature_dimensions_mm.csv
    ("02_CORNICES" 0 (
      (1195.6641 9603.0534) (1111.2824 9603.0534)
    ))
    ; P0166 -- see feature_dimensions_mm.csv
    ("02_CORNICES" 0 (
      (1115.771 6977.0992) (1200.3817 6977.0992)
    ))
    ; P0167 -- see feature_dimensions_mm.csv
    ("02_CORNICES" 0 (
      (1115.771 6977.0992) (1115.771 6656.4885)
    ))
    ; P0168 -- see feature_dimensions_mm.csv
    ("02_CORNICES" 0 (
      (1200.3817 6656.4885) (1115.771 6656.4885)
    ))
    ; P0169 -- see feature_dimensions_mm.csv
    ("02_CORNICES" 0 (
      (1195.6641 9938.9313) (1280.0305 9938.9313)
    ))
    ; P0170 -- see feature_dimensions_mm.csv
    ("02_CORNICES" 0 (
      (1195.6641 9938.9313) (1195.6641 9923.6641)
    ))
    ; P0171 -- see feature_dimensions_mm.csv
    ("02_CORNICES" 0 (
      (1280.0305 9923.6641) (1195.6641 9923.6641)
    ))
    ; P0172 -- see feature_dimensions_mm.csv
    ("02_CORNICES" 0 (
      (1195.6641 9923.6641) (1195.6641 9603.0534)
    ))
    ; P0173 -- see feature_dimensions_mm.csv
    ("02_CORNICES" 0 (
      (1280.0305 9603.0534) (1195.6641 9603.0534)
    ))
    ; P0174 -- see feature_dimensions_mm.csv
    ("02_CORNICES" 0 (
      (1200.3817 6977.0992) (1284.9924 6977.0992)
    ))
    ; P0175 -- see feature_dimensions_mm.csv
    ("02_CORNICES" 0 (
      (1200.3817 6977.0992) (1200.3817 6656.4885)
    ))
    ; P0176 -- see feature_dimensions_mm.csv
    ("02_CORNICES" 0 (
      (1284.9924 6656.4885) (1200.3817 6656.4885)
    ))
    ; P0177 -- see feature_dimensions_mm.csv
    ("02_CORNICES" 0 (
      (1280.0305 9938.9313) (1364.3969 9938.9313)
    ))
    ; P0178 -- see feature_dimensions_mm.csv
    ("02_CORNICES" 0 (
      (1280.0305 9938.9313) (1280.0305 9923.6641)
    ))
    ; P0179 -- see feature_dimensions_mm.csv
    ("02_CORNICES" 0 (
      (1364.3969 9923.6641) (1280.0305 9923.6641)
    ))
    ; P0180 -- see feature_dimensions_mm.csv
    ("02_CORNICES" 0 (
      (1280.0305 9923.6641) (1280.0305 9603.0534)
    ))
    ; P0181 -- see feature_dimensions_mm.csv
    ("02_CORNICES" 0 (
      (1364.3969 9603.0534) (1280.0305 9603.0534)
    ))
    ; P0182 -- see feature_dimensions_mm.csv
    ("02_CORNICES" 0 (
      (1284.9924 6977.0992) (1369.5878 6977.0992)
    ))
    ; P0183 -- see feature_dimensions_mm.csv
    ("02_CORNICES" 0 (
      (1284.9924 6977.0992) (1284.9924 6656.4885)
    ))
    ; P0184 -- see feature_dimensions_mm.csv
    ("02_CORNICES" 0 (
      (1369.5878 6656.4885) (1284.9924 6656.4885)
    ))
    ; P0185 -- see feature_dimensions_mm.csv
    ("02_CORNICES" 0 (
      (1684.4122 2061.0687) (1740.458 2061.0687) (1664.1221 1969.4656) (1664.1221 1862.5954) (1435.1145 1862.5954)
      (1404.5802 1862.5954) (1343.5115 1969.4656)
    ))
    ; P0186 -- see feature_dimensions_mm.csv
    ("02_CORNICES" 0 (
      (1389.313 3679.3893) (1389.313 3740.458) (1358.7786 3740.458)
    ))
    ; P0187 -- see feature_dimensions_mm.csv
    ("02_CORNICES" 0 (
      (1364.3969 9938.9313) (1448.7786 9938.9313)
    ))
    ; P0188 -- see feature_dimensions_mm.csv
    ("02_CORNICES" 0 (
      (1364.3969 9938.9313) (1364.3969 9923.6641)
    ))
    ; P0189 -- see feature_dimensions_mm.csv
    ("02_CORNICES" 0 (
      (1448.7786 9923.6641) (1364.3969 9923.6641)
    ))
    ; P0190 -- see feature_dimensions_mm.csv
    ("02_CORNICES" 0 (
      (1364.3969 9923.6641) (1364.3969 9603.0534)
    ))
    ; P0191 -- see feature_dimensions_mm.csv
    ("02_CORNICES" 0 (
      (1448.7786 9603.0534) (1364.3969 9603.0534)
    ))
    ; P0192 -- see feature_dimensions_mm.csv
    ("02_CORNICES" 0 (
      (1369.5878 6977.0992) (1454.1985 6977.0992)
    ))
    ; P0193 -- see feature_dimensions_mm.csv
    ("02_CORNICES" 0 (
      (1369.5878 6977.0992) (1369.5878 6656.4885)
    ))
    ; P0194 -- see feature_dimensions_mm.csv
    ("02_CORNICES" 0 (
      (1454.1985 6656.4885) (1369.5878 6656.4885)
    ))
    ; P0195 -- see feature_dimensions_mm.csv
    ("02_CORNICES" 0 (
      (1389.313 3679.3893) (1969.4656 3679.3893) (3984.7328 3679.3893) (4564.8855 3679.3893)
    ))
    ; P0196 -- see feature_dimensions_mm.csv
    ("02_CORNICES" 0 (
      (1389.313 3633.5878) (1389.313 3679.3893)
    ))
    ; P0197 -- see feature_dimensions_mm.csv
    ("02_CORNICES" 0 (
      (1389.313 3633.5878) (1969.4656 3633.5878) (3984.7328 3633.5878) (4564.8855 3633.5878)
    ))
    ; P0198 -- see feature_dimensions_mm.csv
    ("02_CORNICES" 0 (
      (1435.4046 8076.3359) (1460.2443 7996.9466) (1485.0687 7996.9466) (1505.7557 7877.8626) (1559.5725 7877.8626)
      (1580.2595 7996.9466) (1600.9618 7996.9466) (1621.6489 8076.3359)
    ))
    ; P0199 -- see feature_dimensions_mm.csv
    ("02_CORNICES" 0 (
      (1448.7786 9938.9313) (1533.145 9938.9313)
    ))
    ; P0200 -- see feature_dimensions_mm.csv
    ("02_CORNICES" 0 (
      (1448.7786 9938.9313) (1448.7786 9923.6641)
    ))
    ; P0201 -- see feature_dimensions_mm.csv
    ("02_CORNICES" 0 (
      (1533.145 9923.6641) (1448.7786 9923.6641)
    ))
    ; P0202 -- see feature_dimensions_mm.csv
    ("02_CORNICES" 0 (
      (1448.7786 9923.6641) (1448.7786 9603.0534)
    ))
    ; P0203 -- see feature_dimensions_mm.csv
    ("02_CORNICES" 0 (
      (1533.145 9603.0534) (1448.7786 9603.0534)
    ))
    ; P0204 -- see feature_dimensions_mm.csv
    ("02_CORNICES" 0 (
      (1454.1985 6977.0992) (1538.8092 6977.0992)
    ))
    ; P0205 -- see feature_dimensions_mm.csv
    ("02_CORNICES" 0 (
      (1454.1985 6977.0992) (1454.1985 6656.4885)
    ))
    ; P0206 -- see feature_dimensions_mm.csv
    ("02_CORNICES" 0 (
      (1538.8092 6656.4885) (1454.1985 6656.4885)
    ))
    ; P0207 -- see feature_dimensions_mm.csv
    ("02_CORNICES" 0 (
      (1533.145 9938.9313) (1617.5115 9938.9313)
    ))
    ; P0208 -- see feature_dimensions_mm.csv
    ("02_CORNICES" 0 (
      (1533.145 9938.9313) (1533.145 9923.6641)
    ))
    ; P0209 -- see feature_dimensions_mm.csv
    ("02_CORNICES" 0 (
      (1617.5115 9923.6641) (1533.145 9923.6641)
    ))
    ; P0210 -- see feature_dimensions_mm.csv
    ("02_CORNICES" 0 (
      (1533.145 9923.6641) (1533.145 9603.0534)
    ))
    ; P0211 -- see feature_dimensions_mm.csv
    ("02_CORNICES" 0 (
      (1617.5115 9603.0534) (1533.145 9603.0534)
    ))
    ; P0212 -- see feature_dimensions_mm.csv
    ("02_CORNICES" 0 (
      (1538.8092 6977.0992) (1623.4046 6977.0992)
    ))
    ; P0213 -- see feature_dimensions_mm.csv
    ("02_CORNICES" 0 (
      (1538.8092 6977.0992) (1538.8092 6656.4885)
    ))
    ; P0214 -- see feature_dimensions_mm.csv
    ("02_CORNICES" 0 (
      (1623.4046 6656.4885) (1538.8092 6656.4885)
    ))
    ; P0215 -- see feature_dimensions_mm.csv
    ("02_CORNICES" 0 (
      (1617.5115 9938.9313) (1701.8931 9938.9313)
    ))
    ; P0216 -- see feature_dimensions_mm.csv
    ("02_CORNICES" 0 (
      (1617.5115 9938.9313) (1617.5115 9923.6641)
    ))
    ; P0217 -- see feature_dimensions_mm.csv
    ("02_CORNICES" 0 (
      (1701.8931 9923.6641) (1617.5115 9923.6641)
    ))
    ; P0218 -- see feature_dimensions_mm.csv
    ("02_CORNICES" 0 (
      (1617.5115 9923.6641) (1617.5115 9603.0534)
    ))
    ; P0219 -- see feature_dimensions_mm.csv
    ("02_CORNICES" 0 (
      (1701.8931 9603.0534) (1617.5115 9603.0534)
    ))
    ; P0220 -- see feature_dimensions_mm.csv
    ("02_CORNICES" 0 (
      (1623.4046 6977.0992) (1708.0153 6977.0992)
    ))
    ; P0221 -- see feature_dimensions_mm.csv
    ("02_CORNICES" 0 (
      (1623.4046 6977.0992) (1623.4046 6656.4885)
    ))
    ; P0222 -- see feature_dimensions_mm.csv
    ("02_CORNICES" 0 (
      (1708.0153 6656.4885) (1623.4046 6656.4885)
    ))
    ; P0223 -- see feature_dimensions_mm.csv
    ("02_CORNICES" 0 (
      (1701.8931 9938.9313) (1786.2595 9938.9313)
    ))
    ; P0224 -- see feature_dimensions_mm.csv
    ("02_CORNICES" 0 (
      (1701.8931 9938.9313) (1701.8931 9923.6641)
    ))
    ; P0225 -- see feature_dimensions_mm.csv
    ("02_CORNICES" 0 (
      (1786.2595 9923.6641) (1701.8931 9923.6641)
    ))
    ; P0226 -- see feature_dimensions_mm.csv
    ("02_CORNICES" 0 (
      (1701.8931 9923.6641) (1701.8931 9603.0534)
    ))
    ; P0227 -- see feature_dimensions_mm.csv
    ("02_CORNICES" 0 (
      (1786.2595 9603.0534) (1701.8931 9603.0534)
    ))
    ; P0228 -- see feature_dimensions_mm.csv
    ("02_CORNICES" 0 (
      (1708.0153 6977.0992) (1792.626 6977.0992)
    ))
    ; P0229 -- see feature_dimensions_mm.csv
    ("02_CORNICES" 0 (
      (1708.0153 6977.0992) (1708.0153 6656.4885)
    ))
    ; P0230 -- see feature_dimensions_mm.csv
    ("02_CORNICES" 0 (
      (1792.626 6656.4885) (1708.0153 6656.4885)
    ))
    ; P0231 -- see feature_dimensions_mm.csv
    ("02_CORNICES" 0 (
      (1786.2595 9938.9313) (1870.626 9938.9313)
    ))
    ; P0232 -- see feature_dimensions_mm.csv
    ("02_CORNICES" 0 (
      (1786.2595 9938.9313) (1786.2595 9923.6641)
    ))
    ; P0233 -- see feature_dimensions_mm.csv
    ("02_CORNICES" 0 (
      (1870.626 9923.6641) (1786.2595 9923.6641)
    ))
    ; P0234 -- see feature_dimensions_mm.csv
    ("02_CORNICES" 0 (
      (1786.2595 9923.6641) (1786.2595 9603.0534)
    ))
    ; P0235 -- see feature_dimensions_mm.csv
    ("02_CORNICES" 0 (
      (1870.626 9603.0534) (1786.2595 9603.0534)
    ))
    ; P0236 -- see feature_dimensions_mm.csv
    ("02_CORNICES" 0 (
      (1792.626 6977.0992) (1877.2214 6977.0992)
    ))
    ; P0237 -- see feature_dimensions_mm.csv
    ("02_CORNICES" 0 (
      (1792.626 6977.0992) (1792.626 6656.4885)
    ))
    ; P0238 -- see feature_dimensions_mm.csv
    ("02_CORNICES" 0 (
      (1877.2214 6656.4885) (1792.626 6656.4885)
    ))
    ; P0239 -- see feature_dimensions_mm.csv
    ("02_CORNICES" 0 (
      (1849.2824 8076.3359) (1874.1221 7996.9466) (1898.9466 7996.9466) (1919.6336 7877.8626) (1973.4504 7877.8626)
      (1994.1374 7996.9466) (2014.8397 7996.9466) (2035.5267 8076.3359)
    ))
    ; P0240 -- see feature_dimensions_mm.csv
    ("02_CORNICES" 0 (
      (1870.626 9938.9313) (1955.0076 9938.9313)
    ))
    ; P0241 -- see feature_dimensions_mm.csv
    ("02_CORNICES" 0 (
      (1870.626 9938.9313) (1870.626 9923.6641)
    ))
    ; P0242 -- see feature_dimensions_mm.csv
    ("02_CORNICES" 0 (
      (1955.0076 9923.6641) (1870.626 9923.6641)
    ))
    ; P0243 -- see feature_dimensions_mm.csv
    ("02_CORNICES" 0 (
      (1870.626 9923.6641) (1870.626 9603.0534)
    ))
    ; P0244 -- see feature_dimensions_mm.csv
    ("02_CORNICES" 0 (
      (1955.0076 9603.0534) (1870.626 9603.0534)
    ))
    ; P0245 -- see feature_dimensions_mm.csv
    ("02_CORNICES" 0 (
      (1877.2214 6977.0992) (1961.8321 6977.0992)
    ))
    ; P0246 -- see feature_dimensions_mm.csv
    ("02_CORNICES" 0 (
      (1877.2214 6977.0992) (1877.2214 6656.4885)
    ))
    ; P0247 -- see feature_dimensions_mm.csv
    ("02_CORNICES" 0 (
      (1961.8321 6656.4885) (1877.2214 6656.4885)
    ))
    ; P0248 -- see feature_dimensions_mm.csv
    ("02_CORNICES" 0 (
      (1955.0076 9938.9313) (2039.374 9938.9313)
    ))
    ; P0249 -- see feature_dimensions_mm.csv
    ("02_CORNICES" 0 (
      (1955.0076 9938.9313) (1955.0076 9923.6641)
    ))
    ; P0250 -- see feature_dimensions_mm.csv
    ("02_CORNICES" 0 (
      (2039.374 9923.6641) (1955.0076 9923.6641)
    ))
    ; P0251 -- see feature_dimensions_mm.csv
    ("02_CORNICES" 0 (
      (1955.0076 9923.6641) (1955.0076 9603.0534)
    ))
    ; P0252 -- see feature_dimensions_mm.csv
    ("02_CORNICES" 0 (
      (2039.374 9603.0534) (1955.0076 9603.0534)
    ))
    ; P0253 -- see feature_dimensions_mm.csv
    ("02_CORNICES" 0 (
      (1961.8321 6977.0992) (2046.4427 6977.0992)
    ))
    ; P0254 -- see feature_dimensions_mm.csv
    ("02_CORNICES" 0 (
      (1961.8321 6977.0992) (1961.8321 6656.4885)
    ))
    ; P0255 -- see feature_dimensions_mm.csv
    ("02_CORNICES" 0 (
      (2046.4427 6656.4885) (1961.8321 6656.4885)
    ))
    ; P0256 -- see feature_dimensions_mm.csv
    ("02_CORNICES" 0 (
      (2039.374 9938.9313) (2123.7405 9938.9313)
    ))
    ; P0257 -- see feature_dimensions_mm.csv
    ("02_CORNICES" 0 (
      (2039.374 9938.9313) (2039.374 9923.6641)
    ))
    ; P0258 -- see feature_dimensions_mm.csv
    ("02_CORNICES" 0 (
      (2123.7405 9923.6641) (2039.374 9923.6641)
    ))
    ; P0259 -- see feature_dimensions_mm.csv
    ("02_CORNICES" 0 (
      (2039.374 9923.6641) (2039.374 9603.0534)
    ))
    ; P0260 -- see feature_dimensions_mm.csv
    ("02_CORNICES" 0 (
      (2123.7405 9603.0534) (2039.374 9603.0534)
    ))
    ; P0261 -- see feature_dimensions_mm.csv
    ("02_CORNICES" 0 (
      (2046.4427 6977.0992) (2131.0382 6977.0992)
    ))
    ; P0262 -- see feature_dimensions_mm.csv
    ("02_CORNICES" 0 (
      (2046.4427 6977.0992) (2046.4427 6656.4885)
    ))
    ; P0263 -- see feature_dimensions_mm.csv
    ("02_CORNICES" 0 (
      (2131.0382 6656.4885) (2046.4427 6656.4885)
    ))
    ; P0264 -- see feature_dimensions_mm.csv
    ("02_CORNICES" 0 (
      (2123.7405 9938.9313) (2208.1221 9938.9313)
    ))
    ; P0265 -- see feature_dimensions_mm.csv
    ("02_CORNICES" 0 (
      (2123.7405 9938.9313) (2123.7405 9923.6641)
    ))
    ; P0266 -- see feature_dimensions_mm.csv
    ("02_CORNICES" 0 (
      (2208.1221 9923.6641) (2123.7405 9923.6641)
    ))
    ; P0267 -- see feature_dimensions_mm.csv
    ("02_CORNICES" 0 (
      (2123.7405 9923.6641) (2123.7405 9603.0534)
    ))
    ; P0268 -- see feature_dimensions_mm.csv
    ("02_CORNICES" 0 (
      (2208.1221 9603.0534) (2123.7405 9603.0534)
    ))
    ; P0269 -- see feature_dimensions_mm.csv
    ("02_CORNICES" 0 (
      (2131.0382 6977.0992) (2215.6489 6977.0992)
    ))
    ; P0270 -- see feature_dimensions_mm.csv
    ("02_CORNICES" 0 (
      (2131.0382 6977.0992) (2131.0382 6656.4885)
    ))
    ; P0271 -- see feature_dimensions_mm.csv
    ("02_CORNICES" 0 (
      (2215.6489 6656.4885) (2131.0382 6656.4885)
    ))
    ; P0272 -- see feature_dimensions_mm.csv
    ("02_CORNICES" 0 (
      (2162.2595 2373.2977) (2150.1985 2433.2366) (2114.5038 2610.687) (2404.5802 2610.687) (2368.8855 2433.2366)
      (2356.8244 2373.2977)
    ))
    ; P0273 -- see feature_dimensions_mm.csv
    ("02_CORNICES" 0 (
      (2352.3664 2351.145) (2166.7176 2351.145)
    ))
    ; P0274 -- see feature_dimensions_mm.csv
    ("02_CORNICES" 0 (
      (2208.1221 9938.9313) (2292.4885 9938.9313)
    ))
    ; P0275 -- see feature_dimensions_mm.csv
    ("02_CORNICES" 0 (
      (2208.1221 9938.9313) (2208.1221 9923.6641)
    ))
    ; P0276 -- see feature_dimensions_mm.csv
    ("02_CORNICES" 0 (
      (2292.4885 9923.6641) (2208.1221 9923.6641)
    ))
    ; P0277 -- see feature_dimensions_mm.csv
    ("02_CORNICES" 0 (
      (2208.1221 9923.6641) (2208.1221 9603.0534)
    ))
    ; P0278 -- see feature_dimensions_mm.csv
    ("02_CORNICES" 0 (
      (2292.4885 9603.0534) (2208.1221 9603.0534)
    ))
    ; P0279 -- see feature_dimensions_mm.csv
    ("02_CORNICES" 0 (
      (2215.6489 6977.0992) (2300.2595 6977.0992)
    ))
    ; P0280 -- see feature_dimensions_mm.csv
    ("02_CORNICES" 0 (
      (2215.6489 6977.0992) (2215.6489 6656.4885)
    ))
    ; P0281 -- see feature_dimensions_mm.csv
    ("02_CORNICES" 0 (
      (2300.2595 6656.4885) (2215.6489 6656.4885)
    ))
    ; P0282 -- see feature_dimensions_mm.csv
    ("02_CORNICES" 0 (
      (2263.1603 8076.3359) (2288.0 7996.9466) (2312.8244 7996.9466) (2333.5267 7877.8626) (2387.3282 7877.8626)
      (2408.0153 7996.9466) (2428.7176 7996.9466) (2449.4046 8076.3359)
    ))
    ; P0283 -- see feature_dimensions_mm.csv
    ("02_CORNICES" 0 (
      (2292.4885 9938.9313) (2376.855 9938.9313)
    ))
    ; P0284 -- see feature_dimensions_mm.csv
    ("02_CORNICES" 0 (
      (2292.4885 9938.9313) (2292.4885 9923.6641)
    ))
    ; P0285 -- see feature_dimensions_mm.csv
    ("02_CORNICES" 0 (
      (2376.855 9923.6641) (2292.4885 9923.6641)
    ))
    ; P0286 -- see feature_dimensions_mm.csv
    ("02_CORNICES" 0 (
      (2292.4885 9923.6641) (2292.4885 9603.0534)
    ))
    ; P0287 -- see feature_dimensions_mm.csv
    ("02_CORNICES" 0 (
      (2376.855 9603.0534) (2292.4885 9603.0534)
    ))
    ; P0288 -- see feature_dimensions_mm.csv
    ("02_CORNICES" 0 (
      (2300.2595 6977.0992) (2384.855 6977.0992)
    ))
    ; P0289 -- see feature_dimensions_mm.csv
    ("02_CORNICES" 0 (
      (2300.2595 6977.0992) (2300.2595 6656.4885)
    ))
    ; P0290 -- see feature_dimensions_mm.csv
    ("02_CORNICES" 0 (
      (2384.855 6656.4885) (2300.2595 6656.4885)
    ))
    ; P0291 -- see feature_dimensions_mm.csv
    ("02_CORNICES" 0 (
      (2376.855 9938.9313) (2461.2366 9938.9313)
    ))
    ; P0292 -- see feature_dimensions_mm.csv
    ("02_CORNICES" 0 (
      (2376.855 9938.9313) (2376.855 9923.6641)
    ))
    ; P0293 -- see feature_dimensions_mm.csv
    ("02_CORNICES" 0 (
      (2461.2366 9923.6641) (2376.855 9923.6641)
    ))
    ; P0294 -- see feature_dimensions_mm.csv
    ("02_CORNICES" 0 (
      (2376.855 9923.6641) (2376.855 9603.0534)
    ))
    ; P0295 -- see feature_dimensions_mm.csv
    ("02_CORNICES" 0 (
      (2461.2366 9603.0534) (2376.855 9603.0534)
    ))
    ; P0296 -- see feature_dimensions_mm.csv
    ("02_CORNICES" 0 (
      (2384.855 6977.0992) (2469.4656 6977.0992)
    ))
    ; P0297 -- see feature_dimensions_mm.csv
    ("02_CORNICES" 0 (
      (2384.855 6977.0992) (2384.855 6656.4885)
    ))
    ; P0298 -- see feature_dimensions_mm.csv
    ("02_CORNICES" 0 (
      (2469.4656 6656.4885) (2384.855 6656.4885)
    ))
    ; P0299 -- see feature_dimensions_mm.csv
    ("02_CORNICES" 0 (
      (2461.2366 9938.9313) (2545.6031 9938.9313)
    ))
    ; P0300 -- see feature_dimensions_mm.csv
    ("02_CORNICES" 0 (
      (2461.2366 9938.9313) (2461.2366 9923.6641)
    ))
    ; P0301 -- see feature_dimensions_mm.csv
    ("02_CORNICES" 0 (
      (2545.6031 9923.6641) (2461.2366 9923.6641)
    ))
    ; P0302 -- see feature_dimensions_mm.csv
    ("02_CORNICES" 0 (
      (2461.2366 9923.6641) (2461.2366 9603.0534)
    ))
    ; P0303 -- see feature_dimensions_mm.csv
    ("02_CORNICES" 0 (
      (2545.6031 9603.0534) (2461.2366 9603.0534)
    ))
    ; P0304 -- see feature_dimensions_mm.csv
    ("02_CORNICES" 0 (
      (2469.4656 6977.0992) (2554.0763 6977.0992)
    ))
    ; P0305 -- see feature_dimensions_mm.csv
    ("02_CORNICES" 0 (
      (2469.4656 6977.0992) (2469.4656 6656.4885)
    ))
    ; P0306 -- see feature_dimensions_mm.csv
    ("02_CORNICES" 0 (
      (2554.0763 6656.4885) (2469.4656 6656.4885)
    ))
    ; P0307 -- see feature_dimensions_mm.csv
    ("02_CORNICES" 0 (
      (2545.6031 9938.9313) (2629.9695 9938.9313)
    ))
    ; P0308 -- see feature_dimensions_mm.csv
    ("02_CORNICES" 0 (
      (2545.6031 9938.9313) (2545.6031 9923.6641)
    ))
    ; P0309 -- see feature_dimensions_mm.csv
    ("02_CORNICES" 0 (
      (2629.9695 9923.6641) (2545.6031 9923.6641)
    ))
    ; P0310 -- see feature_dimensions_mm.csv
    ("02_CORNICES" 0 (
      (2545.6031 9923.6641) (2545.6031 9603.0534)
    ))
    ; P0311 -- see feature_dimensions_mm.csv
    ("02_CORNICES" 0 (
      (2629.9695 9603.0534) (2545.6031 9603.0534)
    ))
    ; P0312 -- see feature_dimensions_mm.csv
    ("02_CORNICES" 0 (
      (2554.0763 6977.0992) (2638.6718 6977.0992)
    ))
    ; P0313 -- see feature_dimensions_mm.csv
    ("02_CORNICES" 0 (
      (2554.0763 6977.0992) (2554.0763 6656.4885)
    ))
    ; P0314 -- see feature_dimensions_mm.csv
    ("02_CORNICES" 0 (
      (2638.6718 6656.4885) (2554.0763 6656.4885)
    ))
    ; P0315 -- see feature_dimensions_mm.csv
    ("02_CORNICES" 0 (
      (2629.9695 9938.9313) (2714.3359 9938.9313)
    ))
    ; P0316 -- see feature_dimensions_mm.csv
    ("02_CORNICES" 0 (
      (2629.9695 9938.9313) (2629.9695 9923.6641)
    ))
    ; P0317 -- see feature_dimensions_mm.csv
    ("02_CORNICES" 0 (
      (2714.3359 9923.6641) (2629.9695 9923.6641)
    ))
    ; P0318 -- see feature_dimensions_mm.csv
    ("02_CORNICES" 0 (
      (2629.9695 9923.6641) (2629.9695 9603.0534)
    ))
    ; P0319 -- see feature_dimensions_mm.csv
    ("02_CORNICES" 0 (
      (2714.3359 9603.0534) (2629.9695 9603.0534)
    ))
    ; P0320 -- see feature_dimensions_mm.csv
    ("02_CORNICES" 0 (
      (2638.6718 6977.0992) (2723.2824 6977.0992)
    ))
    ; P0321 -- see feature_dimensions_mm.csv
    ("02_CORNICES" 0 (
      (2638.6718 6977.0992) (2638.6718 6656.4885)
    ))
    ; P0322 -- see feature_dimensions_mm.csv
    ("02_CORNICES" 0 (
      (2723.2824 6656.4885) (2638.6718 6656.4885)
    ))
    ; P0323 -- see feature_dimensions_mm.csv
    ("02_CORNICES" 0 (
      (2677.0382 8076.3359) (2701.8779 7996.9466) (2726.7023 7996.9466) (2747.4046 7877.8626) (2801.2061 7877.8626)
      (2821.8931 7996.9466) (2842.5954 7996.9466) (2863.2824 8076.3359)
    ))
    ; P0324 -- see feature_dimensions_mm.csv
    ("02_CORNICES" 0 (
      (2714.3359 9938.9313) (2798.7176 9938.9313)
    ))
    ; P0325 -- see feature_dimensions_mm.csv
    ("02_CORNICES" 0 (
      (2714.3359 9938.9313) (2714.3359 9923.6641)
    ))
    ; P0326 -- see feature_dimensions_mm.csv
    ("02_CORNICES" 0 (
      (2798.7176 9923.6641) (2714.3359 9923.6641)
    ))
    ; P0327 -- see feature_dimensions_mm.csv
    ("02_CORNICES" 0 (
      (2714.3359 9923.6641) (2714.3359 9603.0534)
    ))
    ; P0328 -- see feature_dimensions_mm.csv
    ("02_CORNICES" 0 (
      (2798.7176 9603.0534) (2714.3359 9603.0534)
    ))
    ; P0329 -- see feature_dimensions_mm.csv
    ("02_CORNICES" 0 (
      (2723.2824 6977.0992) (2807.8931 6977.0992)
    ))
    ; P0330 -- see feature_dimensions_mm.csv
    ("02_CORNICES" 0 (
      (2723.2824 6977.0992) (2723.2824 6656.4885)
    ))
    ; P0331 -- see feature_dimensions_mm.csv
    ("02_CORNICES" 0 (
      (2807.8931 6656.4885) (2723.2824 6656.4885)
    ))
    ; P0332 -- see feature_dimensions_mm.csv
    ("02_CORNICES" 0 (
      (2778.626 2061.0687) (2834.6718 2061.0687)
    ))
    ; P0333 -- see feature_dimensions_mm.csv
    ("02_CORNICES" 0 (
      (2798.7176 9938.9313) (2883.084 9938.9313)
    ))
    ; P0334 -- see feature_dimensions_mm.csv
    ("02_CORNICES" 0 (
      (2798.7176 9938.9313) (2798.7176 9923.6641)
    ))
    ; P0335 -- see feature_dimensions_mm.csv
    ("02_CORNICES" 0 (
      (2883.084 9923.6641) (2798.7176 9923.6641)
    ))
    ; P0336 -- see feature_dimensions_mm.csv
    ("02_CORNICES" 0 (
      (2798.7176 9923.6641) (2798.7176 9603.0534)
    ))
    ; P0337 -- see feature_dimensions_mm.csv
    ("02_CORNICES" 0 (
      (2883.084 9603.0534) (2798.7176 9603.0534)
    ))
    ; P0338 -- see feature_dimensions_mm.csv
    ("02_CORNICES" 0 (
      (2807.8931 6977.0992) (2892.4885 6977.0992)
    ))
    ; P0339 -- see feature_dimensions_mm.csv
    ("02_CORNICES" 0 (
      (2807.8931 6977.0992) (2807.8931 6656.4885)
    ))
    ; P0340 -- see feature_dimensions_mm.csv
    ("02_CORNICES" 0 (
      (2892.4885 6656.4885) (2807.8931 6656.4885)
    ))
    ; P0341 -- see feature_dimensions_mm.csv
    ("02_CORNICES" 0 (
      (2931.0229 5938.9313) (2824.4275 5938.9313) (2840.2137 5864.4122)
    ))
    ; P0342 -- see feature_dimensions_mm.csv
    ("02_CORNICES" 0 (
      (2847.9542 5827.8321) (2857.4504 5782.9924) (2879.3893 5679.3893)
    ))
    ; P0343 -- see feature_dimensions_mm.csv
    ("02_CORNICES" 0 (
      (2861.2061 1990.2748) (2854.7481 1995.8321)
    ))
    ; P0344 -- see feature_dimensions_mm.csv
    ("02_CORNICES" 0 (
      (2883.084 9938.9313) (2967.4504 9938.9313)
    ))
    ; P0345 -- see feature_dimensions_mm.csv
    ("02_CORNICES" 0 (
      (2883.084 9938.9313) (2883.084 9923.6641)
    ))
    ; P0346 -- see feature_dimensions_mm.csv
    ("02_CORNICES" 0 (
      (2967.4504 9923.6641) (2883.084 9923.6641)
    ))
    ; P0347 -- see feature_dimensions_mm.csv
    ("02_CORNICES" 0 (
      (2883.084 9923.6641) (2883.084 9603.0534)
    ))
    ; P0348 -- see feature_dimensions_mm.csv
    ("02_CORNICES" 0 (
      (2967.4504 9603.0534) (2883.084 9603.0534)
    ))
    ; P0349 -- see feature_dimensions_mm.csv
    ("02_CORNICES" 0 (
      (3114.5038 1862.5954) (2946.5649 1862.5954) (2885.4962 1969.4656)
    ))
    ; P0350 -- see feature_dimensions_mm.csv
    ("02_CORNICES" 0 (
      (2892.4885 6977.0992) (2977.0992 6977.0992)
    ))
    ; P0351 -- see feature_dimensions_mm.csv
    ("02_CORNICES" 0 (
      (2892.4885 6977.0992) (2892.4885 6656.4885)
    ))
    ; P0352 -- see feature_dimensions_mm.csv
    ("02_CORNICES" 0 (
      (2977.0992 6656.4885) (2892.4885 6656.4885)
    ))
    ; P0353 -- see feature_dimensions_mm.csv
    ("02_CORNICES" 0 (
      (2967.4504 9938.9313) (3051.8321 9938.9313)
    ))
    ; P0354 -- see feature_dimensions_mm.csv
    ("02_CORNICES" 0 (
      (2967.4504 9938.9313) (2967.4504 9923.6641)
    ))
    ; P0355 -- see feature_dimensions_mm.csv
    ("02_CORNICES" 0 (
      (3051.8321 9923.6641) (2967.4504 9923.6641)
    ))
    ; P0356 -- see feature_dimensions_mm.csv
    ("02_CORNICES" 0 (
      (2967.4504 9923.6641) (2967.4504 9603.0534)
    ))
    ; P0357 -- see feature_dimensions_mm.csv
    ("02_CORNICES" 0 (
      (3051.8321 9603.0534) (2967.4504 9603.0534)
    ))
    ; P0358 -- see feature_dimensions_mm.csv
    ("02_CORNICES" 0 (
      (2977.0992 6977.0992) (3061.7099 6977.0992)
    ))
    ; P0359 -- see feature_dimensions_mm.csv
    ("02_CORNICES" 0 (
      (2977.0992 6977.0992) (2977.0992 6656.4885)
    ))
    ; P0360 -- see feature_dimensions_mm.csv
    ("02_CORNICES" 0 (
      (3061.7099 6656.4885) (2977.0992 6656.4885)
    ))
    ; P0361 -- see feature_dimensions_mm.csv
    ("02_CORNICES" 0 (
      (3051.8321 9938.9313) (3136.1985 9938.9313)
    ))
    ; P0362 -- see feature_dimensions_mm.csv
    ("02_CORNICES" 0 (
      (3051.8321 9938.9313) (3051.8321 9923.6641)
    ))
    ; P0363 -- see feature_dimensions_mm.csv
    ("02_CORNICES" 0 (
      (3136.1985 9923.6641) (3051.8321 9923.6641)
    ))
    ; P0364 -- see feature_dimensions_mm.csv
    ("02_CORNICES" 0 (
      (3051.8321 9923.6641) (3051.8321 9603.0534)
    ))
    ; P0365 -- see feature_dimensions_mm.csv
    ("02_CORNICES" 0 (
      (3136.1985 9603.0534) (3051.8321 9603.0534)
    ))
    ; P0366 -- see feature_dimensions_mm.csv
    ("02_CORNICES" 0 (
      (3108.3206 5837.6641) (3129.771 5938.9313) (3055.8321 5938.9313)
    ))
    ; P0367 -- see feature_dimensions_mm.csv
    ("02_CORNICES" 0 (
      (3061.7099 6977.0992) (3146.3053 6977.0992)
    ))
    ; P0368 -- see feature_dimensions_mm.csv
    ("02_CORNICES" 0 (
      (3061.7099 6977.0992) (3061.7099 6656.4885)
    ))
    ; P0369 -- see feature_dimensions_mm.csv
    ("02_CORNICES" 0 (
      (3146.3053 6656.4885) (3061.7099 6656.4885)
    ))
    ; P0370 -- see feature_dimensions_mm.csv
    ("02_CORNICES" 0 (
      (3074.8092 5679.3893) (3096.7481 5782.9924) (3106.2443 5827.8321)
    ))
    ; P0371 -- see feature_dimensions_mm.csv
    ("02_CORNICES" 0 (
      (3090.916 8076.3359) (3115.7557 7996.9466) (3140.5802 7996.9466) (3161.2824 7877.8626) (3215.084 7877.8626)
      (3235.771 7996.9466) (3256.4733 7996.9466) (3277.1603 8076.3359)
    ))
    ; P0372 -- see feature_dimensions_mm.csv
    ("02_CORNICES" 0 (
      (3136.1985 9938.9313) (3220.5649 9938.9313)
    ))
    ; P0373 -- see feature_dimensions_mm.csv
    ("02_CORNICES" 0 (
      (3136.1985 9938.9313) (3136.1985 9923.6641)
    ))
    ; P0374 -- see feature_dimensions_mm.csv
    ("02_CORNICES" 0 (
      (3220.5649 9923.6641) (3136.1985 9923.6641)
    ))
    ; P0375 -- see feature_dimensions_mm.csv
    ("02_CORNICES" 0 (
      (3136.1985 9923.6641) (3136.1985 9603.0534)
    ))
    ; P0376 -- see feature_dimensions_mm.csv
    ("02_CORNICES" 0 (
      (3220.5649 9603.0534) (3136.1985 9603.0534)
    ))
    ; P0377 -- see feature_dimensions_mm.csv
    ("02_CORNICES" 0 (
      (3146.3053 6977.0992) (3230.916 6977.0992)
    ))
    ; P0378 -- see feature_dimensions_mm.csv
    ("02_CORNICES" 0 (
      (3146.3053 6977.0992) (3146.3053 6656.4885)
    ))
    ; P0379 -- see feature_dimensions_mm.csv
    ("02_CORNICES" 0 (
      (3230.916 6656.4885) (3146.3053 6656.4885)
    ))
    ; P0380 -- see feature_dimensions_mm.csv
    ("02_CORNICES" 0 (
      (3220.5649 9938.9313) (3304.9466 9938.9313)
    ))
    ; P0381 -- see feature_dimensions_mm.csv
    ("02_CORNICES" 0 (
      (3220.5649 9938.9313) (3220.5649 9923.6641)
    ))
    ; P0382 -- see feature_dimensions_mm.csv
    ("02_CORNICES" 0 (
      (3304.9466 9923.6641) (3220.5649 9923.6641)
    ))
    ; P0383 -- see feature_dimensions_mm.csv
    ("02_CORNICES" 0 (
      (3220.5649 9923.6641) (3220.5649 9603.0534)
    ))
    ; P0384 -- see feature_dimensions_mm.csv
    ("02_CORNICES" 0 (
      (3304.9466 9603.0534) (3220.5649 9603.0534)
    ))
    ; P0385 -- see feature_dimensions_mm.csv
    ("02_CORNICES" 0 (
      (3230.916 6977.0992) (3315.5267 6977.0992)
    ))
    ; P0386 -- see feature_dimensions_mm.csv
    ("02_CORNICES" 0 (
      (3230.916 6977.0992) (3230.916 6656.4885)
    ))
    ; P0387 -- see feature_dimensions_mm.csv
    ("02_CORNICES" 0 (
      (3315.5267 6656.4885) (3230.916 6656.4885)
    ))
    ; P0388 -- see feature_dimensions_mm.csv
    ("02_CORNICES" 0 (
      (3304.9466 9938.9313) (3389.313 9938.9313)
    ))
    ; P0389 -- see feature_dimensions_mm.csv
    ("02_CORNICES" 0 (
      (3304.9466 9938.9313) (3304.9466 9923.6641)
    ))
    ; P0390 -- see feature_dimensions_mm.csv
    ("02_CORNICES" 0 (
      (3389.313 9923.6641) (3304.9466 9923.6641)
    ))
    ; P0391 -- see feature_dimensions_mm.csv
    ("02_CORNICES" 0 (
      (3304.9466 9923.6641) (3304.9466 9603.0534)
    ))
    ; P0392 -- see feature_dimensions_mm.csv
    ("02_CORNICES" 0 (
      (3389.313 9603.0534) (3304.9466 9603.0534)
    ))
    ; P0393 -- see feature_dimensions_mm.csv
    ("02_CORNICES" 0 (
      (3315.5267 6977.0992) (3400.1221 6977.0992)
    ))
    ; P0394 -- see feature_dimensions_mm.csv
    ("02_CORNICES" 0 (
      (3315.5267 6977.0992) (3315.5267 6656.4885)
    ))
    ; P0395 -- see feature_dimensions_mm.csv
    ("02_CORNICES" 0 (
      (3400.1221 6656.4885) (3315.5267 6656.4885)
    ))
    ; P0396 -- see feature_dimensions_mm.csv
    ("02_CORNICES" 0 (
      (3389.313 9938.9313) (3473.6794 9938.9313)
    ))
    ; P0397 -- see feature_dimensions_mm.csv
    ("02_CORNICES" 0 (
      (3389.313 9938.9313) (3389.313 9923.6641)
    ))
    ; P0398 -- see feature_dimensions_mm.csv
    ("02_CORNICES" 0 (
      (3473.6794 9923.6641) (3389.313 9923.6641)
    ))
    ; P0399 -- see feature_dimensions_mm.csv
    ("02_CORNICES" 0 (
      (3389.313 9923.6641) (3389.313 9603.0534)
    ))
    ; P0400 -- see feature_dimensions_mm.csv
    ("02_CORNICES" 0 (
      (3473.6794 9603.0534) (3389.313 9603.0534)
    ))
    ; P0401 -- see feature_dimensions_mm.csv
    ("02_CORNICES" 0 (
      (3400.1221 6977.0992) (3484.7328 6977.0992)
    ))
    ; P0402 -- see feature_dimensions_mm.csv
    ("02_CORNICES" 0 (
      (3400.1221 6977.0992) (3400.1221 6656.4885)
    ))
    ; P0403 -- see feature_dimensions_mm.csv
    ("02_CORNICES" 0 (
      (3484.7328 6656.4885) (3400.1221 6656.4885)
    ))
    ; P0404 -- see feature_dimensions_mm.csv
    ("02_CORNICES" 0 (
      (3473.6794 9938.9313) (3558.0611 9938.9313)
    ))
    ; P0405 -- see feature_dimensions_mm.csv
    ("02_CORNICES" 0 (
      (3473.6794 9938.9313) (3473.6794 9923.6641)
    ))
    ; P0406 -- see feature_dimensions_mm.csv
    ("02_CORNICES" 0 (
      (3558.0611 9923.6641) (3473.6794 9923.6641)
    ))
    ; P0407 -- see feature_dimensions_mm.csv
    ("02_CORNICES" 0 (
      (3473.6794 9923.6641) (3473.6794 9603.0534)
    ))
    ; P0408 -- see feature_dimensions_mm.csv
    ("02_CORNICES" 0 (
      (3558.0611 9603.0534) (3473.6794 9603.0534)
    ))
    ; P0409 -- see feature_dimensions_mm.csv
    ("02_CORNICES" 0 (
      (3484.7328 6977.0992) (3569.3435 6977.0992)
    ))
    ; P0410 -- see feature_dimensions_mm.csv
    ("02_CORNICES" 0 (
      (3484.7328 6977.0992) (3484.7328 6656.4885)
    ))
    ; P0411 -- see feature_dimensions_mm.csv
    ("02_CORNICES" 0 (
      (3569.3435 6656.4885) (3484.7328 6656.4885)
    ))
    ; P0412 -- see feature_dimensions_mm.csv
    ("02_CORNICES" 0 (
      (3504.7939 8076.3359) (3529.6336 7996.9466) (3554.458 7996.9466) (3575.1603 7877.8626) (3628.9618 7877.8626)
      (3649.6489 7996.9466) (3670.3511 7996.9466) (3691.0382 8076.3359)
    ))
    ; P0413 -- see feature_dimensions_mm.csv
    ("02_CORNICES" 0 (
      (3541.9847 2625.9542) (3832.0611 2625.9542)
    ))
    ; P0414 -- see feature_dimensions_mm.csv
    ("02_CORNICES" 0 (
      (3558.0611 9938.9313) (3642.4275 9938.9313)
    ))
    ; P0415 -- see feature_dimensions_mm.csv
    ("02_CORNICES" 0 (
      (3558.0611 9938.9313) (3558.0611 9923.6641)
    ))
    ; P0416 -- see feature_dimensions_mm.csv
    ("02_CORNICES" 0 (
      (3642.4275 9923.6641) (3558.0611 9923.6641)
    ))
    ; P0417 -- see feature_dimensions_mm.csv
    ("02_CORNICES" 0 (
      (3558.0611 9923.6641) (3558.0611 9603.0534)
    ))
    ; P0418 -- see feature_dimensions_mm.csv
    ("02_CORNICES" 0 (
      (3642.4275 9603.0534) (3558.0611 9603.0534)
    ))
    ; P0419 -- see feature_dimensions_mm.csv
    ("02_CORNICES" 0 (
      (3569.3435 6977.0992) (3653.9389 6977.0992)
    ))
    ; P0420 -- see feature_dimensions_mm.csv
    ("02_CORNICES" 0 (
      (3569.3435 6977.0992) (3569.3435 6656.4885)
    ))
    ; P0421 -- see feature_dimensions_mm.csv
    ("02_CORNICES" 0 (
      (3653.9389 6656.4885) (3569.3435 6656.4885)
    ))
    ; P0422 -- see feature_dimensions_mm.csv
    ("02_CORNICES" 0 (
      (3593.5573 2384.7023) (3574.3053 2474.7328)
    ))
    ; P0423 -- see feature_dimensions_mm.csv
    ("02_CORNICES" 0 (
      (3779.8473 2381.6794) (3594.1985 2381.6794)
    ))
    ; P0424 -- see feature_dimensions_mm.csv
    ("02_CORNICES" 0 (
      (3642.4275 9938.9313) (3726.7939 9938.9313)
    ))
    ; P0425 -- see feature_dimensions_mm.csv
    ("02_CORNICES" 0 (
      (3642.4275 9938.9313) (3642.4275 9923.6641)
    ))
    ; P0426 -- see feature_dimensions_mm.csv
    ("02_CORNICES" 0 (
      (3726.7939 9923.6641) (3642.4275 9923.6641)
    ))
    ; P0427 -- see feature_dimensions_mm.csv
    ("02_CORNICES" 0 (
      (3642.4275 9923.6641) (3642.4275 9603.0534)
    ))
    ; P0428 -- see feature_dimensions_mm.csv
    ("02_CORNICES" 0 (
      (3726.7939 9603.0534) (3642.4275 9603.0534)
    ))
    ; P0429 -- see feature_dimensions_mm.csv
    ("02_CORNICES" 0 (
      (3653.9389 6977.0992) (3738.5496 6977.0992)
    ))
    ; P0430 -- see feature_dimensions_mm.csv
    ("02_CORNICES" 0 (
      (3653.9389 6977.0992) (3653.9389 6656.4885)
    ))
    ; P0431 -- see feature_dimensions_mm.csv
    ("02_CORNICES" 0 (
      (3738.5496 6656.4885) (3653.9389 6656.4885)
    ))
    ; P0432 -- see feature_dimensions_mm.csv
    ("02_CORNICES" 0 (
      (3726.7939 9938.9313) (3811.1756 9938.9313)
    ))
    ; P0433 -- see feature_dimensions_mm.csv
    ("02_CORNICES" 0 (
      (3726.7939 9938.9313) (3726.7939 9923.6641)
    ))
    ; P0434 -- see feature_dimensions_mm.csv
    ("02_CORNICES" 0 (
      (3811.1756 9923.6641) (3726.7939 9923.6641)
    ))
    ; P0435 -- see feature_dimensions_mm.csv
    ("02_CORNICES" 0 (
      (3726.7939 9923.6641) (3726.7939 9603.0534)
    ))
    ; P0436 -- see feature_dimensions_mm.csv
    ("02_CORNICES" 0 (
      (3811.1756 9603.0534) (3726.7939 9603.0534)
    ))
    ; P0437 -- see feature_dimensions_mm.csv
    ("02_CORNICES" 0 (
      (3738.5496 6977.0992) (3823.1603 6977.0992)
    ))
    ; P0438 -- see feature_dimensions_mm.csv
    ("02_CORNICES" 0 (
      (3738.5496 6977.0992) (3738.5496 6656.4885)
    ))
    ; P0439 -- see feature_dimensions_mm.csv
    ("02_CORNICES" 0 (
      (3823.1603 6656.4885) (3738.5496 6656.4885)
    ))
    ; P0440 -- see feature_dimensions_mm.csv
    ("02_CORNICES" 0 (
      (3799.7405 2474.7328) (3780.4885 2384.7023)
    ))
    ; P0441 -- see feature_dimensions_mm.csv
    ("02_CORNICES" 0 (
      (3811.1756 9938.9313) (3895.542 9938.9313)
    ))
    ; P0442 -- see feature_dimensions_mm.csv
    ("02_CORNICES" 0 (
      (3811.1756 9938.9313) (3811.1756 9923.6641)
    ))
    ; P0443 -- see feature_dimensions_mm.csv
    ("02_CORNICES" 0 (
      (3895.542 9923.6641) (3811.1756 9923.6641)
    ))
    ; P0444 -- see feature_dimensions_mm.csv
    ("02_CORNICES" 0 (
      (3811.1756 9923.6641) (3811.1756 9603.0534)
    ))
    ; P0445 -- see feature_dimensions_mm.csv
    ("02_CORNICES" 0 (
      (3895.542 9603.0534) (3811.1756 9603.0534)
    ))
    ; P0446 -- see feature_dimensions_mm.csv
    ("02_CORNICES" 0 (
      (3823.1603 6977.0992) (3907.7557 6977.0992)
    ))
    ; P0447 -- see feature_dimensions_mm.csv
    ("02_CORNICES" 0 (
      (3823.1603 6977.0992) (3823.1603 6656.4885)
    ))
    ; P0448 -- see feature_dimensions_mm.csv
    ("02_CORNICES" 0 (
      (3907.7557 6656.4885) (3823.1603 6656.4885)
    ))
    ; P0449 -- see feature_dimensions_mm.csv
    ("02_CORNICES" 0 (
      (3895.542 9938.9313) (3979.9084 9938.9313)
    ))
    ; P0450 -- see feature_dimensions_mm.csv
    ("02_CORNICES" 0 (
      (3895.542 9938.9313) (3895.542 9923.6641)
    ))
    ; P0451 -- see feature_dimensions_mm.csv
    ("02_CORNICES" 0 (
      (3979.9084 9923.6641) (3895.542 9923.6641)
    ))
    ; P0452 -- see feature_dimensions_mm.csv
    ("02_CORNICES" 0 (
      (3895.542 9923.6641) (3895.542 9603.0534)
    ))
    ; P0453 -- see feature_dimensions_mm.csv
    ("02_CORNICES" 0 (
      (3979.9084 9603.0534) (3895.542 9603.0534)
    ))
    ; P0454 -- see feature_dimensions_mm.csv
    ("02_CORNICES" 0 (
      (3907.7557 6977.0992) (3992.3664 6977.0992)
    ))
    ; P0455 -- see feature_dimensions_mm.csv
    ("02_CORNICES" 0 (
      (3907.7557 6977.0992) (3907.7557 6656.4885)
    ))
    ; P0456 -- see feature_dimensions_mm.csv
    ("02_CORNICES" 0 (
      (3992.3664 6656.4885) (3907.7557 6656.4885)
    ))
    ; P0457 -- see feature_dimensions_mm.csv
    ("02_CORNICES" 0 (
      (3918.6718 8076.3359) (3943.5115 7996.9466) (3968.3359 7996.9466) (3989.0382 7877.8626) (4042.8397 7877.8626)
      (4063.5267 7996.9466) (4084.229 7996.9466) (4104.916 8076.3359)
    ))
    ; P0458 -- see feature_dimensions_mm.csv
    ("02_CORNICES" 0 (
      (3979.9084 9938.9313) (4064.2901 9938.9313)
    ))
    ; P0459 -- see feature_dimensions_mm.csv
    ("02_CORNICES" 0 (
      (3979.9084 9938.9313) (3979.9084 9923.6641)
    ))
    ; P0460 -- see feature_dimensions_mm.csv
    ("02_CORNICES" 0 (
      (4064.2901 9923.6641) (3979.9084 9923.6641)
    ))
    ; P0461 -- see feature_dimensions_mm.csv
    ("02_CORNICES" 0 (
      (3979.9084 9923.6641) (3979.9084 9603.0534)
    ))
    ; P0462 -- see feature_dimensions_mm.csv
    ("02_CORNICES" 0 (
      (4064.2901 9603.0534) (3979.9084 9603.0534)
    ))
    ; P0463 -- see feature_dimensions_mm.csv
    ("02_CORNICES" 0 (
      (3992.3664 6977.0992) (4076.9771 6977.0992)
    ))
    ; P0464 -- see feature_dimensions_mm.csv
    ("02_CORNICES" 0 (
      (3992.3664 6977.0992) (3992.3664 6656.4885)
    ))
    ; P0465 -- see feature_dimensions_mm.csv
    ("02_CORNICES" 0 (
      (4076.9771 6656.4885) (3992.3664 6656.4885)
    ))
    ; P0466 -- see feature_dimensions_mm.csv
    ("02_CORNICES" 0 (
      (4064.2901 9938.9313) (4148.6565 9938.9313)
    ))
    ; P0467 -- see feature_dimensions_mm.csv
    ("02_CORNICES" 0 (
      (4064.2901 9938.9313) (4064.2901 9923.6641)
    ))
    ; P0468 -- see feature_dimensions_mm.csv
    ("02_CORNICES" 0 (
      (4148.6565 9923.6641) (4064.2901 9923.6641)
    ))
    ; P0469 -- see feature_dimensions_mm.csv
    ("02_CORNICES" 0 (
      (4064.2901 9923.6641) (4064.2901 9603.0534)
    ))
    ; P0470 -- see feature_dimensions_mm.csv
    ("02_CORNICES" 0 (
      (4148.6565 9603.0534) (4064.2901 9603.0534)
    ))
    ; P0471 -- see feature_dimensions_mm.csv
    ("02_CORNICES" 0 (
      (4076.9771 6977.0992) (4161.5725 6977.0992)
    ))
    ; P0472 -- see feature_dimensions_mm.csv
    ("02_CORNICES" 0 (
      (4076.9771 6977.0992) (4076.9771 6656.4885)
    ))
    ; P0473 -- see feature_dimensions_mm.csv
    ("02_CORNICES" 0 (
      (4161.5725 6656.4885) (4076.9771 6656.4885)
    ))
    ; P0474 -- see feature_dimensions_mm.csv
    ("02_CORNICES" 0 (
      (4148.6565 9938.9313) (4233.0229 9938.9313)
    ))
    ; P0475 -- see feature_dimensions_mm.csv
    ("02_CORNICES" 0 (
      (4148.6565 9938.9313) (4148.6565 9923.6641)
    ))
    ; P0476 -- see feature_dimensions_mm.csv
    ("02_CORNICES" 0 (
      (4233.0229 9923.6641) (4148.6565 9923.6641)
    ))
    ; P0477 -- see feature_dimensions_mm.csv
    ("02_CORNICES" 0 (
      (4148.6565 9923.6641) (4148.6565 9603.0534)
    ))
    ; P0478 -- see feature_dimensions_mm.csv
    ("02_CORNICES" 0 (
      (4233.0229 9603.0534) (4148.6565 9603.0534)
    ))
    ; P0479 -- see feature_dimensions_mm.csv
    ("02_CORNICES" 0 (
      (4161.5725 6977.0992) (4246.1832 6977.0992)
    ))
    ; P0480 -- see feature_dimensions_mm.csv
    ("02_CORNICES" 0 (
      (4161.5725 6977.0992) (4161.5725 6656.4885)
    ))
    ; P0481 -- see feature_dimensions_mm.csv
    ("02_CORNICES" 0 (
      (4246.1832 6656.4885) (4161.5725 6656.4885)
    ))
    ; P0482 -- see feature_dimensions_mm.csv
    ("02_CORNICES" 0 (
      (4233.0229 9938.9313) (4317.3893 9938.9313)
    ))
    ; P0483 -- see feature_dimensions_mm.csv
    ("02_CORNICES" 0 (
      (4233.0229 9938.9313) (4233.0229 9923.6641)
    ))
    ; P0484 -- see feature_dimensions_mm.csv
    ("02_CORNICES" 0 (
      (4317.3893 9923.6641) (4233.0229 9923.6641)
    ))
    ; P0485 -- see feature_dimensions_mm.csv
    ("02_CORNICES" 0 (
      (4233.0229 9923.6641) (4233.0229 9603.0534)
    ))
    ; P0486 -- see feature_dimensions_mm.csv
    ("02_CORNICES" 0 (
      (4317.3893 9603.0534) (4233.0229 9603.0534)
    ))
    ; P0487 -- see feature_dimensions_mm.csv
    ("02_CORNICES" 0 (
      (4246.1832 6977.0992) (4330.7939 6977.0992)
    ))
    ; P0488 -- see feature_dimensions_mm.csv
    ("02_CORNICES" 0 (
      (4246.1832 6977.0992) (4246.1832 6656.4885)
    ))
    ; P0489 -- see feature_dimensions_mm.csv
    ("02_CORNICES" 0 (
      (4330.7939 6656.4885) (4246.1832 6656.4885)
    ))
    ; P0490 -- see feature_dimensions_mm.csv
    ("02_CORNICES" 0 (
      (4317.3893 9938.9313) (4401.771 9938.9313)
    ))
    ; P0491 -- see feature_dimensions_mm.csv
    ("02_CORNICES" 0 (
      (4317.3893 9938.9313) (4317.3893 9923.6641)
    ))
    ; P0492 -- see feature_dimensions_mm.csv
    ("02_CORNICES" 0 (
      (4401.771 9923.6641) (4317.3893 9923.6641)
    ))
    ; P0493 -- see feature_dimensions_mm.csv
    ("02_CORNICES" 0 (
      (4317.3893 9923.6641) (4317.3893 9603.0534)
    ))
    ; P0494 -- see feature_dimensions_mm.csv
    ("02_CORNICES" 0 (
      (4401.771 9603.0534) (4317.3893 9603.0534)
    ))
    ; P0495 -- see feature_dimensions_mm.csv
    ("02_CORNICES" 0 (
      (4330.7939 6977.0992) (4415.3893 6977.0992)
    ))
    ; P0496 -- see feature_dimensions_mm.csv
    ("02_CORNICES" 0 (
      (4330.7939 6977.0992) (4330.7939 6656.4885)
    ))
    ; P0497 -- see feature_dimensions_mm.csv
    ("02_CORNICES" 0 (
      (4415.3893 6656.4885) (4330.7939 6656.4885)
    ))
    ; P0498 -- see feature_dimensions_mm.csv
    ("02_CORNICES" 0 (
      (4332.5496 8076.3359) (4357.3893 7996.9466) (4382.2137 7996.9466) (4402.916 7877.8626) (4456.7176 7877.8626)
      (4477.4046 7996.9466) (4498.1069 7996.9466) (4518.7939 8076.3359)
    ))
    ; P0499 -- see feature_dimensions_mm.csv
    ("02_CORNICES" 0 (
      (4519.084 1862.5954) (4351.145 1862.5954)
    ))
    ; P0500 -- see feature_dimensions_mm.csv
    ("02_CORNICES" 0 (
      (4401.771 9938.9313) (4486.1374 9938.9313)
    ))
    ; P0501 -- see feature_dimensions_mm.csv
    ("02_CORNICES" 0 (
      (4401.771 9938.9313) (4401.771 9923.6641)
    ))
    ; P0502 -- see feature_dimensions_mm.csv
    ("02_CORNICES" 0 (
      (4486.1374 9923.6641) (4401.771 9923.6641)
    ))
    ; P0503 -- see feature_dimensions_mm.csv
    ("02_CORNICES" 0 (
      (4401.771 9923.6641) (4401.771 9603.0534)
    ))
    ; P0504 -- see feature_dimensions_mm.csv
    ("02_CORNICES" 0 (
      (4486.1374 9603.0534) (4401.771 9603.0534)
    ))
    ; P0505 -- see feature_dimensions_mm.csv
    ("02_CORNICES" 0 (
      (4415.3893 6977.0992) (4500.0 6977.0992)
    ))
    ; P0506 -- see feature_dimensions_mm.csv
    ("02_CORNICES" 0 (
      (4415.3893 6977.0992) (4415.3893 6656.4885)
    ))
    ; P0507 -- see feature_dimensions_mm.csv
    ("02_CORNICES" 0 (
      (4500.0 6656.4885) (4415.3893 6656.4885)
    ))
    ; P0508 -- see feature_dimensions_mm.csv
    ("02_CORNICES" 0 (
      (4486.1374 9938.9313) (4570.5038 9938.9313)
    ))
    ; P0509 -- see feature_dimensions_mm.csv
    ("02_CORNICES" 0 (
      (4486.1374 9938.9313) (4486.1374 9923.6641)
    ))
    ; P0510 -- see feature_dimensions_mm.csv
    ("02_CORNICES" 0 (
      (4570.5038 9923.6641) (4486.1374 9923.6641)
    ))
    ; P0511 -- see feature_dimensions_mm.csv
    ("02_CORNICES" 0 (
      (4486.1374 9923.6641) (4486.1374 9603.0534)
    ))
    ; P0512 -- see feature_dimensions_mm.csv
    ("02_CORNICES" 0 (
      (4570.5038 9603.0534) (4486.1374 9603.0534)
    ))
    ; P0513 -- see feature_dimensions_mm.csv
    ("02_CORNICES" 0 (
      (4500.0 6977.0992) (4584.6107 6977.0992)
    ))
    ; P0514 -- see feature_dimensions_mm.csv
    ("02_CORNICES" 0 (
      (4500.0 6977.0992) (4500.0 6656.4885)
    ))
    ; P0515 -- see feature_dimensions_mm.csv
    ("02_CORNICES" 0 (
      (4584.6107 6656.4885) (4500.0 6656.4885)
    ))
    ; P0516 -- see feature_dimensions_mm.csv
    ("02_CORNICES" 0 (
      (4564.8855 3679.3893) (4595.4198 3679.3893) (4992.3664 3679.3893) (5022.9008 3679.3893)
    ))
    ; P0517 -- see feature_dimensions_mm.csv
    ("02_CORNICES" 0 (
      (4564.8855 3679.3893) (4564.8855 3633.5878)
    ))
    ; P0518 -- see feature_dimensions_mm.csv
    ("02_CORNICES" 0 (
      (4595.4198 3740.458) (4564.8855 3740.458) (4564.8855 3679.3893)
    ))
    ; P0519 -- see feature_dimensions_mm.csv
    ("02_CORNICES" 0 (
      (4564.8855 3633.5878) (4595.4198 3633.5878) (4992.3664 3633.5878) (5022.9008 3633.5878)
    ))
    ; P0520 -- see feature_dimensions_mm.csv
    ("02_CORNICES" 0 (
      (4570.5038 9938.9313) (4654.8855 9938.9313)
    ))
    ; P0521 -- see feature_dimensions_mm.csv
    ("02_CORNICES" 0 (
      (4570.5038 9938.9313) (4570.5038 9923.6641)
    ))
    ; P0522 -- see feature_dimensions_mm.csv
    ("02_CORNICES" 0 (
      (4654.8855 9923.6641) (4570.5038 9923.6641)
    ))
    ; P0523 -- see feature_dimensions_mm.csv
    ("02_CORNICES" 0 (
      (4570.5038 9923.6641) (4570.5038 9603.0534)
    ))
    ; P0524 -- see feature_dimensions_mm.csv
    ("02_CORNICES" 0 (
      (4654.8855 9603.0534) (4570.5038 9603.0534)
    ))
    ; P0525 -- see feature_dimensions_mm.csv
    ("02_CORNICES" 0 (
      (4584.6107 6977.0992) (4669.2061 6977.0992)
    ))
    ; P0526 -- see feature_dimensions_mm.csv
    ("02_CORNICES" 0 (
      (4584.6107 6977.0992) (4584.6107 6656.4885)
    ))
    ; P0527 -- see feature_dimensions_mm.csv
    ("02_CORNICES" 0 (
      (4669.2061 6656.4885) (4584.6107 6656.4885)
    ))
    ; P0528 -- see feature_dimensions_mm.csv
    ("02_CORNICES" 0 (
      (4654.8855 9938.9313) (4739.2519 9938.9313)
    ))
    ; P0529 -- see feature_dimensions_mm.csv
    ("02_CORNICES" 0 (
      (4654.8855 9938.9313) (4654.8855 9923.6641)
    ))
    ; P0530 -- see feature_dimensions_mm.csv
    ("02_CORNICES" 0 (
      (4739.2519 9923.6641) (4654.8855 9923.6641)
    ))
    ; P0531 -- see feature_dimensions_mm.csv
    ("02_CORNICES" 0 (
      (4654.8855 9923.6641) (4654.8855 9603.0534)
    ))
    ; P0532 -- see feature_dimensions_mm.csv
    ("02_CORNICES" 0 (
      (4739.2519 9603.0534) (4654.8855 9603.0534)
    ))
    ; P0533 -- see feature_dimensions_mm.csv
    ("02_CORNICES" 0 (
      (4669.2061 6977.0992) (4753.8168 6977.0992)
    ))
    ; P0534 -- see feature_dimensions_mm.csv
    ("02_CORNICES" 0 (
      (4669.2061 6977.0992) (4669.2061 6656.4885)
    ))
    ; P0535 -- see feature_dimensions_mm.csv
    ("02_CORNICES" 0 (
      (4753.8168 6656.4885) (4669.2061 6656.4885)
    ))
    ; P0536 -- see feature_dimensions_mm.csv
    ("02_CORNICES" 0 (
      (4739.2519 9938.9313) (4823.6183 9938.9313)
    ))
    ; P0537 -- see feature_dimensions_mm.csv
    ("02_CORNICES" 0 (
      (4739.2519 9938.9313) (4739.2519 9923.6641)
    ))
    ; P0538 -- see feature_dimensions_mm.csv
    ("02_CORNICES" 0 (
      (4823.6183 9923.6641) (4739.2519 9923.6641)
    ))
    ; P0539 -- see feature_dimensions_mm.csv
    ("02_CORNICES" 0 (
      (4739.2519 9923.6641) (4739.2519 9603.0534)
    ))
    ; P0540 -- see feature_dimensions_mm.csv
    ("02_CORNICES" 0 (
      (4823.6183 9603.0534) (4739.2519 9603.0534)
    ))
    ; P0541 -- see feature_dimensions_mm.csv
    ("02_CORNICES" 0 (
      (4746.4275 8076.3359) (4771.2672 7996.9466) (4796.0916 7996.9466) (4816.7939 7877.8626) (4870.5954 7877.8626)
      (4891.2824 7996.9466) (4911.9847 7996.9466) (4932.6718 8076.3359)
    ))
    ; P0542 -- see feature_dimensions_mm.csv
    ("02_CORNICES" 0 (
      (4753.8168 6977.0992) (4838.4275 6977.0992)
    ))
    ; P0543 -- see feature_dimensions_mm.csv
    ("02_CORNICES" 0 (
      (4753.8168 6977.0992) (4753.8168 6656.4885)
    ))
    ; P0544 -- see feature_dimensions_mm.csv
    ("02_CORNICES" 0 (
      (4838.4275 6656.4885) (4753.8168 6656.4885)
    ))
    ; P0545 -- see feature_dimensions_mm.csv
    ("02_CORNICES" 0 (
      (8687.0229 8320.6107) (4793.8931 8320.6107)
    ))
    ; P0546 -- see feature_dimensions_mm.csv
    ("02_CORNICES" 0 (
      (4977.0992 8137.4046) (4793.8931 8137.4046) (4793.8931 8320.6107)
    ))
    ; P0547 -- see feature_dimensions_mm.csv
    ("02_CORNICES" 0 (
      (4793.8931 8320.6107) (4641.2214 8320.6107) (4641.2214 8503.8168) (4641.2214 8610.687) (4641.2214 8641.2214)
      (4860.0916 8641.2214) (4883.9695 8561.8321) (4907.8473 8561.8321) (4927.7557 8442.7481) (4979.4809 8442.7481)
      (4999.3893 8561.8321) (5019.2824 8561.8321) (5039.1756 8641.2214) (5258.0611 8641.2214) (5281.9389 8561.8321)
      (5305.8168 8561.8321) (5325.7099 8442.7481) (5377.4504 8442.7481) (5397.3435 8561.8321) (5417.2366 8561.8321)
      (5437.145 8641.2214) (5656.0153 8641.2214) (5679.8931 8561.8321) (5703.771 8561.8321) (5723.6641 8442.7481)
      (5775.4046 8442.7481) (5795.2977 8561.8321) (5815.2061 8561.8321) (5835.0992 8641.2214) (6053.9847 8641.2214)
      (6077.8626 8561.8321) (6101.7405 8561.8321) (6121.6336 8442.7481) (6173.3588 8442.7481) (6193.2672 8561.8321)
      (6213.1603 8561.8321) (6233.0534 8641.2214) (6451.9389 8641.2214) (6475.8168 8561.8321) (6499.6947 8561.8321)
      (6519.5878 8442.7481) (6571.3282 8442.7481) (6591.2214 8561.8321) (6611.1145 8561.8321) (6631.0229 8641.2214)
      (6849.8931 8641.2214) (6873.771 8561.8321) (6897.6489 8561.8321) (6917.5573 8442.7481) (6969.2824 8442.7481)
      (6989.1756 8561.8321) (7009.084 8561.8321) (7028.9771 8641.2214) (7247.8626 8641.2214) (7271.7405 8561.8321)
      (7295.6183 8561.8321) (7315.5115 8442.7481) (7367.2519 8442.7481) (7387.145 8561.8321) (7407.0382 8561.8321)
      (7426.9313 8641.2214) (7645.8168 8641.2214) (7669.6947 8561.8321) (7693.5725 8561.8321) (7713.4656 8442.7481)
      (7765.2061 8442.7481) (7785.0992 8561.8321) (7804.9924 8561.8321) (7824.9008 8641.2214) (8043.771 8641.2214)
      (8067.6489 8561.8321) (8091.5267 8561.8321) (8111.4351 8442.7481) (8163.1603 8442.7481) (8183.0687 8561.8321)
      (8202.9618 8561.8321) (8222.855 8641.2214) (8441.7405 8641.2214) (8465.6183 8561.8321) (8489.4962 8561.8321)
      (8509.3893 8442.7481) (8561.1298 8442.7481) (8581.0229 8561.8321) (8600.916 8561.8321) (8620.8244 8641.2214)
      (8839.6947 8641.2214) (8839.6947 8320.6107) (8687.0229 8320.6107)
    ))
    ; P0548 -- see feature_dimensions_mm.csv
    ("02_CORNICES" 0 (
      (4823.6183 9938.9313) (4908.0 9938.9313)
    ))
    ; P0549 -- see feature_dimensions_mm.csv
    ("02_CORNICES" 0 (
      (4823.6183 9938.9313) (4823.6183 9923.6641)
    ))
    ; P0550 -- see feature_dimensions_mm.csv
    ("02_CORNICES" 0 (
      (4908.0 9923.6641) (4823.6183 9923.6641)
    ))
    ; P0551 -- see feature_dimensions_mm.csv
    ("02_CORNICES" 0 (
      (4823.6183 9923.6641) (4823.6183 9603.0534)
    ))
    ; P0552 -- see feature_dimensions_mm.csv
    ("02_CORNICES" 0 (
      (4908.0 9603.0534) (4823.6183 9603.0534)
    ))
    ; P0553 -- see feature_dimensions_mm.csv
    ("02_CORNICES" 0 (
      (4838.4275 6977.0992) (4923.0229 6977.0992)
    ))
    ; P0554 -- see feature_dimensions_mm.csv
    ("02_CORNICES" 0 (
      (4838.4275 6977.0992) (4838.4275 6656.4885)
    ))
    ; P0555 -- see feature_dimensions_mm.csv
    ("02_CORNICES" 0 (
      (4923.0229 6656.4885) (4838.4275 6656.4885)
    ))
    ; P0556 -- see feature_dimensions_mm.csv
    ("02_CORNICES" 0 (
      (4908.0 9938.9313) (4992.3664 9938.9313) (4992.3664 9923.6641)
    ))
    ; P0557 -- see feature_dimensions_mm.csv
    ("02_CORNICES" 0 (
      (4908.0 9938.9313) (4908.0 9923.6641)
    ))
    ; P0558 -- see feature_dimensions_mm.csv
    ("02_CORNICES" 0 (
      (4992.3664 9923.6641) (4908.0 9923.6641)
    ))
    ; P0559 -- see feature_dimensions_mm.csv
    ("02_CORNICES" 0 (
      (4908.0 9923.6641) (4908.0 9603.0534)
    ))
    ; P0560 -- see feature_dimensions_mm.csv
    ("02_CORNICES" 0 (
      (4992.3664 9603.0534) (4908.0 9603.0534)
    ))
    ; P0561 -- see feature_dimensions_mm.csv
    ("02_CORNICES" 0 (
      (4923.0229 6977.0992) (4992.3664 6977.0992) (5007.6336 6977.0992) (5007.6336 6961.8321)
    ))
    ; P0562 -- see feature_dimensions_mm.csv
    ("02_CORNICES" 0 (
      (4923.0229 6977.0992) (4923.0229 6656.4885)
    ))
    ; P0563 -- see feature_dimensions_mm.csv
    ("02_CORNICES" 0 (
      (4992.3664 6656.4885) (4923.0229 6656.4885)
    ))
    ; P0564 -- see feature_dimensions_mm.csv
    ("02_CORNICES" 0 (
      (8671.7557 8137.4046) (4977.0992 8137.4046)
    ))
    ; P0565 -- see feature_dimensions_mm.csv
    ("02_CORNICES" 0 (
      (4977.0992 8137.4046) (4977.0992 8122.1374) (4977.0992 8076.3359) (4992.3664 8076.3359) (5160.3053 8076.3359)
      (5160.3053 7755.7252) (7022.9008 7755.7252)
    ))
    ; P0566 -- see feature_dimensions_mm.csv
    ("02_CORNICES" 0 (
      (5007.6336 9969.4656) (5007.6336 9923.6641) (4992.3664 9923.6641)
    ))
    ; P0567 -- see feature_dimensions_mm.csv
    ("02_CORNICES" 0 (
      (4992.3664 9923.6641) (4992.3664 9603.0534)
    ))
    ; P0568 -- see feature_dimensions_mm.csv
    ("02_CORNICES" 0 (
      (4992.3664 9603.0534) (4992.3664 9587.7863) (4992.3664 9572.5191)
    ))
    ; P0569 -- see feature_dimensions_mm.csv
    ("02_CORNICES" 0 (
      (4992.3664 7374.0458) (8671.7557 7374.0458)
    ))
    ; P0570 -- see feature_dimensions_mm.csv
    ("02_CORNICES" 0 (
      (4992.3664 7312.9771) (8671.7557 7312.9771)
    ))
    ; P0571 -- see feature_dimensions_mm.csv
    ("02_CORNICES" 0 (
      (5007.6336 6656.4885) (4992.3664 6656.4885)
    ))
    ; P0572 -- see feature_dimensions_mm.csv
    ("02_CORNICES" 0 (
      (4992.3664 6625.9542) (4992.3664 6656.4885)
    ))
    ; P0573 -- see feature_dimensions_mm.csv
    ("02_CORNICES" 0 (
      (4992.3664 6656.4885) (4992.3664 6961.8321) (5007.6336 6961.8321)
    ))
    ; P0574 -- see feature_dimensions_mm.csv
    ("02_CORNICES" 0 (
      (5007.6336 6625.9542) (4992.3664 6625.9542)
    ))
    ; P0575 -- see feature_dimensions_mm.csv
    ("02_CORNICES" 0 (
      (4992.3664 6564.8855) (4992.3664 6625.9542)
    ))
    ; P0576 -- see feature_dimensions_mm.csv
    ("02_CORNICES" 0 (
      (5007.6336 6625.9542) (5007.6336 6564.8855) (4992.3664 6564.8855)
    ))
    ; P0577 -- see feature_dimensions_mm.csv
    ("02_CORNICES" 0 (
      (4992.3664 6473.2824) (4992.3664 6564.8855)
    ))
    ; P0578 -- see feature_dimensions_mm.csv
    ("02_CORNICES" 0 (
      (5022.9008 3679.3893) (5022.9008 3740.458) (4992.3664 3740.458)
    ))
    ; P0579 -- see feature_dimensions_mm.csv
    ("02_CORNICES" 0 (
      (5160.3053 10259.542) (5053.4351 10122.1374) (5007.6336 10122.1374)
    ))
    ; P0580 -- see feature_dimensions_mm.csv
    ("02_CORNICES" 0 (
      (5007.6336 10122.1374) (5007.6336 9984.7328)
    ))
    ; P0581 -- see feature_dimensions_mm.csv
    ("02_CORNICES" 0 (
      (5007.6336 9984.7328) (5007.6336 9969.4656)
    ))
    ; P0582 -- see feature_dimensions_mm.csv
    ("02_CORNICES" 0 (
      (5007.6336 6961.8321) (5068.7023 6961.8321)
    ))
    ; P0583 -- see feature_dimensions_mm.csv
    ("02_CORNICES" 0 (
      (5007.6336 6961.8321) (5007.6336 6656.4885)
    ))
    ; P0584 -- see feature_dimensions_mm.csv
    ("02_CORNICES" 0 (
      (5007.6336 6656.4885) (5007.6336 6625.9542)
    ))
    ; P0585 -- see feature_dimensions_mm.csv
    ("02_CORNICES" 0 (
      (5068.7023 6625.9542) (5007.6336 6625.9542)
    ))
    ; P0586 -- see feature_dimensions_mm.csv
    ("02_CORNICES" 0 (
      (5022.9008 3679.3893) (5114.5038 3679.3893) (5114.5038 3633.5878)
    ))
    ; P0587 -- see feature_dimensions_mm.csv
    ("02_CORNICES" 0 (
      (5022.9008 3633.5878) (5022.9008 3679.3893)
    ))
    ; P0588 -- see feature_dimensions_mm.csv
    ("02_CORNICES" 0 (
      (5022.9008 3633.5878) (5114.5038 3633.5878)
    ))
    ; P0589 -- see feature_dimensions_mm.csv
    ("02_CORNICES" 0 (
      (5068.7023 6961.8321) (5099.2366 6961.8321)
    ))
    ; P0590 -- see feature_dimensions_mm.csv
    ("02_CORNICES" 0 (
      (5068.7023 6625.9542) (5068.7023 6961.8321)
    ))
    ; P0591 -- see feature_dimensions_mm.csv
    ("02_CORNICES" 0 (
      (5099.2366 6625.9542) (5068.7023 6625.9542)
    ))
    ; P0592 -- see feature_dimensions_mm.csv
    ("02_CORNICES" 0 (
      (5099.2366 6961.8321) (5160.3053 6961.8321)
    ))
    ; P0593 -- see feature_dimensions_mm.csv
    ("02_CORNICES" 0 (
      (5099.2366 6961.8321) (5099.2366 6625.9542)
    ))
    ; P0594 -- see feature_dimensions_mm.csv
    ("02_CORNICES" 0 (
      (5160.3053 6625.9542) (5099.2366 6625.9542)
    ))
    ; P0595 -- see feature_dimensions_mm.csv
    ("02_CORNICES" 0 (
      (5114.5038 3633.5878) (5175.5725 3633.5878) (5160.3053 3419.8473) (5137.4046 3389.313)
    ))
    ; P0596 -- see feature_dimensions_mm.csv
    ("02_CORNICES" 0 (
      (5160.3053 7740.458) (5160.3053 7679.3893) (8671.7557 7679.3893) (8671.7557 7740.458)
    ))
    ; P0597 -- see feature_dimensions_mm.csv
    ("02_CORNICES" 1 (
      (5160.3053 7740.458) (5038.1679 7557.2519) (916.0305 7557.2519) (793.8931 7740.458)
    ))
    ; P0598 -- see feature_dimensions_mm.csv
    ("02_CORNICES" 0 (
      (5160.3053 6961.8321) (5190.8397 6961.8321)
    ))
    ; P0599 -- see feature_dimensions_mm.csv
    ("02_CORNICES" 0 (
      (5160.3053 6625.9542) (5160.3053 6961.8321)
    ))
    ; P0600 -- see feature_dimensions_mm.csv
    ("02_CORNICES" 0 (
      (5190.8397 6625.9542) (5160.3053 6625.9542)
    ))
    ; P0601 -- see feature_dimensions_mm.csv
    ("02_CORNICES" 0 (
      (5190.8397 6961.8321) (5251.9084 6961.8321)
    ))
    ; P0602 -- see feature_dimensions_mm.csv
    ("02_CORNICES" 0 (
      (5190.8397 6961.8321) (5190.8397 6625.9542)
    ))
    ; P0603 -- see feature_dimensions_mm.csv
    ("02_CORNICES" 0 (
      (5251.9084 6625.9542) (5190.8397 6625.9542)
    ))
    ; P0604 -- see feature_dimensions_mm.csv
    ("02_CORNICES" 0 (
      (5251.9084 6961.8321) (5268.2595 6961.8321)
    ))
    ; P0605 -- see feature_dimensions_mm.csv
    ("02_CORNICES" 0 (
      (5251.9084 6625.9542) (5251.9084 6961.8321)
    ))
    ; P0606 -- see feature_dimensions_mm.csv
    ("02_CORNICES" 0 (
      (5268.2595 6625.9542) (5251.9084 6625.9542)
    ))
    ; P0607 -- see feature_dimensions_mm.csv
    ("02_CORNICES" 0 (
      (5268.2595 6961.8321) (5282.4427 6961.8321)
    ))
    ; P0608 -- see feature_dimensions_mm.csv
    ("02_CORNICES" 0 (
      (5268.2595 6961.8321) (5268.2595 6625.9542)
    ))
    ; P0609 -- see feature_dimensions_mm.csv
    ("02_CORNICES" 0 (
      (5282.4427 6625.9542) (5268.2595 6625.9542)
    ))
    ; P0610 -- see feature_dimensions_mm.csv
    ("02_CORNICES" 0 (
      (5282.4427 6961.8321) (5343.5115 6961.8321)
    ))
    ; P0611 -- see feature_dimensions_mm.csv
    ("02_CORNICES" 0 (
      (5282.4427 6961.8321) (5282.4427 6625.9542)
    ))
    ; P0612 -- see feature_dimensions_mm.csv
    ("02_CORNICES" 0 (
      (5343.5115 6625.9542) (5282.4427 6625.9542)
    ))
    ; P0613 -- see feature_dimensions_mm.csv
    ("02_CORNICES" 0 (
      (5343.5115 6961.8321) (5374.0458 6961.8321)
    ))
    ; P0614 -- see feature_dimensions_mm.csv
    ("02_CORNICES" 0 (
      (5343.5115 6625.9542) (5343.5115 6961.8321)
    ))
    ; P0615 -- see feature_dimensions_mm.csv
    ("02_CORNICES" 0 (
      (5374.0458 6625.9542) (5343.5115 6625.9542)
    ))
    ; P0616 -- see feature_dimensions_mm.csv
    ("02_CORNICES" 0 (
      (5374.0458 6961.8321) (5435.1145 6961.8321)
    ))
    ; P0617 -- see feature_dimensions_mm.csv
    ("02_CORNICES" 0 (
      (5374.0458 6961.8321) (5374.0458 6625.9542)
    ))
    ; P0618 -- see feature_dimensions_mm.csv
    ("02_CORNICES" 0 (
      (5435.1145 6625.9542) (5374.0458 6625.9542)
    ))
    ; P0619 -- see feature_dimensions_mm.csv
    ("02_CORNICES" 0 (
      (5435.1145 6961.8321) (5465.6489 6961.8321)
    ))
    ; P0620 -- see feature_dimensions_mm.csv
    ("02_CORNICES" 0 (
      (5435.1145 6625.9542) (5435.1145 6961.8321)
    ))
    ; P0621 -- see feature_dimensions_mm.csv
    ("02_CORNICES" 0 (
      (5465.6489 6625.9542) (5435.1145 6625.9542)
    ))
    ; P0622 -- see feature_dimensions_mm.csv
    ("02_CORNICES" 0 (
      (5465.6489 6961.8321) (5544.1679 6961.8321)
    ))
    ; P0623 -- see feature_dimensions_mm.csv
    ("02_CORNICES" 0 (
      (5465.6489 6961.8321) (5465.6489 6625.9542)
    ))
    ; P0624 -- see feature_dimensions_mm.csv
    ("02_CORNICES" 0 (
      (5544.1679 6625.9542) (5465.6489 6625.9542)
    ))
    ; P0625 -- see feature_dimensions_mm.csv
    ("02_CORNICES" 0 (
      (5544.1679 6961.8321) (5820.0611 6961.8321)
    ))
    ; P0626 -- see feature_dimensions_mm.csv
    ("02_CORNICES" 0 (
      (5544.1679 6961.8321) (5544.1679 6625.9542)
    ))
    ; P0627 -- see feature_dimensions_mm.csv
    ("02_CORNICES" 0 (
      (5820.0611 6625.9542) (5544.1679 6625.9542)
    ))
    ; P0628 -- see feature_dimensions_mm.csv
    ("02_CORNICES" 0 (
      (5820.0611 6961.8321) (6095.9695 6961.8321)
    ))
    ; P0629 -- see feature_dimensions_mm.csv
    ("02_CORNICES" 0 (
      (5820.0611 6961.8321) (5820.0611 6625.9542)
    ))
    ; P0630 -- see feature_dimensions_mm.csv
    ("02_CORNICES" 0 (
      (6095.9695 6625.9542) (5820.0611 6625.9542)
    ))
    ; P0631 -- see feature_dimensions_mm.csv
    ("02_CORNICES" 0 (
      (6095.9695 6961.8321) (6371.8626 6961.8321)
    ))
    ; P0632 -- see feature_dimensions_mm.csv
    ("02_CORNICES" 0 (
      (6095.9695 6961.8321) (6095.9695 6625.9542)
    ))
    ; P0633 -- see feature_dimensions_mm.csv
    ("02_CORNICES" 0 (
      (6371.8626 6625.9542) (6095.9695 6625.9542)
    ))
    ; P0634 -- see feature_dimensions_mm.csv
    ("02_CORNICES" 0 (
      (6371.8626 6961.8321) (6647.771 6961.8321)
    ))
    ; P0635 -- see feature_dimensions_mm.csv
    ("02_CORNICES" 0 (
      (6371.8626 6961.8321) (6371.8626 6625.9542)
    ))
    ; P0636 -- see feature_dimensions_mm.csv
    ("02_CORNICES" 0 (
      (6647.771 6625.9542) (6371.8626 6625.9542)
    ))
    ; P0637 -- see feature_dimensions_mm.csv
    ("02_CORNICES" 0 (
      (6647.771 6961.8321) (6923.6641 6961.8321)
    ))
    ; P0638 -- see feature_dimensions_mm.csv
    ("02_CORNICES" 0 (
      (6647.771 6961.8321) (6647.771 6625.9542)
    ))
    ; P0639 -- see feature_dimensions_mm.csv
    ("02_CORNICES" 0 (
      (6923.6641 6625.9542) (6647.771 6625.9542)
    ))
    ; P0640 -- see feature_dimensions_mm.csv
    ("02_CORNICES" 0 (
      (6923.6641 6961.8321) (7199.5573 6961.8321)
    ))
    ; P0641 -- see feature_dimensions_mm.csv
    ("02_CORNICES" 0 (
      (6923.6641 6961.8321) (6923.6641 6625.9542)
    ))
    ; P0642 -- see feature_dimensions_mm.csv
    ("02_CORNICES" 0 (
      (7199.5573 6625.9542) (6923.6641 6625.9542)
    ))
    ; P0643 -- see feature_dimensions_mm.csv
    ("02_CORNICES" 0 (
      (7022.9008 7755.7252) (7039.6947 7755.7252)
    ))
    ; P0644 -- see feature_dimensions_mm.csv
    ("02_CORNICES" 0 (
      (7022.9008 7755.7252) (7022.9008 8122.1374) (7039.6947 8122.1374) (7039.6947 7755.7252)
    ))
    ; P0645 -- see feature_dimensions_mm.csv
    ("02_CORNICES" 0 (
      (7039.6947 7755.7252) (8671.7557 7755.7252) (8671.7557 7923.6641) (8671.7557 8122.1374) (8671.7557 8137.4046)
    ))
    ; P0646 -- see feature_dimensions_mm.csv
    ("02_CORNICES" 0 (
      (7199.5573 6961.8321) (7475.4656 6961.8321)
    ))
    ; P0647 -- see feature_dimensions_mm.csv
    ("02_CORNICES" 0 (
      (7199.5573 6961.8321) (7199.5573 6625.9542)
    ))
    ; P0648 -- see feature_dimensions_mm.csv
    ("02_CORNICES" 0 (
      (7475.4656 6625.9542) (7199.5573 6625.9542)
    ))
    ; P0649 -- see feature_dimensions_mm.csv
    ("02_CORNICES" 0 (
      (7475.4656 6961.8321) (7751.3588 6961.8321)
    ))
    ; P0650 -- see feature_dimensions_mm.csv
    ("02_CORNICES" 0 (
      (7475.4656 6961.8321) (7475.4656 6625.9542)
    ))
    ; P0651 -- see feature_dimensions_mm.csv
    ("02_CORNICES" 0 (
      (7751.3588 6625.9542) (7475.4656 6625.9542)
    ))
    ; P0652 -- see feature_dimensions_mm.csv
    ("02_CORNICES" 0 (
      (7751.3588 6961.8321) (8027.2672 6961.8321)
    ))
    ; P0653 -- see feature_dimensions_mm.csv
    ("02_CORNICES" 0 (
      (7751.3588 6961.8321) (7751.3588 6625.9542)
    ))
    ; P0654 -- see feature_dimensions_mm.csv
    ("02_CORNICES" 0 (
      (8027.2672 6625.9542) (7751.3588 6625.9542)
    ))
    ; P0655 -- see feature_dimensions_mm.csv
    ("02_CORNICES" 0 (
      (8027.2672 6961.8321) (8152.6718 6961.8321)
    ))
    ; P0656 -- see feature_dimensions_mm.csv
    ("02_CORNICES" 0 (
      (8027.2672 6961.8321) (8027.2672 6625.9542)
    ))
    ; P0657 -- see feature_dimensions_mm.csv
    ("02_CORNICES" 0 (
      (8152.6718 6625.9542) (8027.2672 6625.9542)
    ))
    ; P0658 -- see feature_dimensions_mm.csv
    ("02_CORNICES" 0 (
      (8152.6718 6961.8321) (8183.2061 6961.8321)
    ))
    ; P0659 -- see feature_dimensions_mm.csv
    ("02_CORNICES" 0 (
      (8152.6718 6625.9542) (8152.6718 6961.8321)
    ))
    ; P0660 -- see feature_dimensions_mm.csv
    ("02_CORNICES" 0 (
      (8183.2061 6625.9542) (8152.6718 6625.9542)
    ))
    ; P0661 -- see feature_dimensions_mm.csv
    ("02_CORNICES" 0 (
      (8183.2061 6961.8321) (8244.2748 6961.8321)
    ))
    ; P0662 -- see feature_dimensions_mm.csv
    ("02_CORNICES" 0 (
      (8183.2061 6961.8321) (8183.2061 6625.9542)
    ))
    ; P0663 -- see feature_dimensions_mm.csv
    ("02_CORNICES" 0 (
      (8244.2748 6625.9542) (8183.2061 6625.9542)
    ))
    ; P0664 -- see feature_dimensions_mm.csv
    ("02_CORNICES" 0 (
      (8244.2748 6961.8321) (8274.8092 6961.8321)
    ))
    ; P0665 -- see feature_dimensions_mm.csv
    ("02_CORNICES" 0 (
      (8244.2748 6625.9542) (8244.2748 6961.8321)
    ))
    ; P0666 -- see feature_dimensions_mm.csv
    ("02_CORNICES" 0 (
      (8274.8092 6625.9542) (8244.2748 6625.9542)
    ))
    ; P0667 -- see feature_dimensions_mm.csv
    ("02_CORNICES" 0 (
      (8274.8092 6961.8321) (8303.1603 6961.8321)
    ))
    ; P0668 -- see feature_dimensions_mm.csv
    ("02_CORNICES" 0 (
      (8274.8092 6961.8321) (8274.8092 6625.9542)
    ))
    ; P0669 -- see feature_dimensions_mm.csv
    ("02_CORNICES" 0 (
      (8303.1603 6625.9542) (8274.8092 6625.9542)
    ))
    ; P0670 -- see feature_dimensions_mm.csv
    ("02_CORNICES" 0 (
      (8303.1603 6961.8321) (8335.8779 6961.8321)
    ))
    ; P0671 -- see feature_dimensions_mm.csv
    ("02_CORNICES" 0 (
      (8303.1603 6961.8321) (8303.1603 6625.9542)
    ))
    ; P0672 -- see feature_dimensions_mm.csv
    ("02_CORNICES" 0 (
      (8335.8779 6625.9542) (8303.1603 6625.9542)
    ))
    ; P0673 -- see feature_dimensions_mm.csv
    ("02_CORNICES" 0 (
      (8335.8779 6961.8321) (8366.4122 6961.8321)
    ))
    ; P0674 -- see feature_dimensions_mm.csv
    ("02_CORNICES" 0 (
      (8335.8779 6625.9542) (8335.8779 6961.8321)
    ))
    ; P0675 -- see feature_dimensions_mm.csv
    ("02_CORNICES" 0 (
      (8366.4122 6625.9542) (8335.8779 6625.9542)
    ))
    ; P0676 -- see feature_dimensions_mm.csv
    ("02_CORNICES" 0 (
      (8366.4122 6961.8321) (8427.4809 6961.8321)
    ))
    ; P0677 -- see feature_dimensions_mm.csv
    ("02_CORNICES" 0 (
      (8366.4122 6961.8321) (8366.4122 6625.9542)
    ))
    ; P0678 -- see feature_dimensions_mm.csv
    ("02_CORNICES" 0 (
      (8427.4809 6625.9542) (8366.4122 6625.9542)
    ))
    ; P0679 -- see feature_dimensions_mm.csv
    ("02_CORNICES" 0 (
      (8427.4809 6961.8321) (8458.0153 6961.8321)
    ))
    ; P0680 -- see feature_dimensions_mm.csv
    ("02_CORNICES" 0 (
      (8427.4809 6625.9542) (8427.4809 6961.8321)
    ))
    ; P0681 -- see feature_dimensions_mm.csv
    ("02_CORNICES" 0 (
      (8458.0153 6625.9542) (8427.4809 6625.9542)
    ))
    ; P0682 -- see feature_dimensions_mm.csv
    ("02_CORNICES" 0 (
      (8458.0153 6961.8321) (8519.084 6961.8321)
    ))
    ; P0683 -- see feature_dimensions_mm.csv
    ("02_CORNICES" 0 (
      (8458.0153 6961.8321) (8458.0153 6625.9542)
    ))
    ; P0684 -- see feature_dimensions_mm.csv
    ("02_CORNICES" 0 (
      (8519.084 6625.9542) (8458.0153 6625.9542)
    ))
    ; P0685 -- see feature_dimensions_mm.csv
    ("02_CORNICES" 0 (
      (8519.084 6961.8321) (8549.6183 6961.8321)
    ))
    ; P0686 -- see feature_dimensions_mm.csv
    ("02_CORNICES" 0 (
      (8519.084 6625.9542) (8519.084 6961.8321)
    ))
    ; P0687 -- see feature_dimensions_mm.csv
    ("02_CORNICES" 0 (
      (8549.6183 6625.9542) (8519.084 6625.9542)
    ))
    ; P0688 -- see feature_dimensions_mm.csv
    ("02_CORNICES" 0 (
      (8549.6183 6961.8321) (8579.0687 6961.8321)
    ))
    ; P0689 -- see feature_dimensions_mm.csv
    ("02_CORNICES" 0 (
      (8549.6183 6961.8321) (8549.6183 6625.9542)
    ))
    ; P0690 -- see feature_dimensions_mm.csv
    ("02_CORNICES" 0 (
      (8579.0687 6625.9542) (8549.6183 6625.9542)
    ))
    ; P0691 -- see feature_dimensions_mm.csv
    ("02_CORNICES" 0 (
      (8579.0687 6961.8321) (8610.687 6961.8321)
    ))
    ; P0692 -- see feature_dimensions_mm.csv
    ("02_CORNICES" 0 (
      (8579.0687 6961.8321) (8579.0687 6625.9542)
    ))
    ; P0693 -- see feature_dimensions_mm.csv
    ("02_CORNICES" 0 (
      (8610.687 6625.9542) (8579.0687 6625.9542)
    ))
    ; P0694 -- see feature_dimensions_mm.csv
    ("02_CORNICES" 0 (
      (8610.687 6961.8321) (8641.2214 6961.8321)
    ))
    ; P0695 -- see feature_dimensions_mm.csv
    ("02_CORNICES" 0 (
      (8610.687 6625.9542) (8610.687 6961.8321)
    ))
    ; P0696 -- see feature_dimensions_mm.csv
    ("02_CORNICES" 0 (
      (8641.2214 6625.9542) (8610.687 6625.9542)
    ))
    ; P0697 -- see feature_dimensions_mm.csv
    ("02_CORNICES" 0 (
      (8641.2214 6961.8321) (8671.7557 6961.8321) (8702.2901 6961.8321)
    ))
    ; P0698 -- see feature_dimensions_mm.csv
    ("02_CORNICES" 0 (
      (8641.2214 6961.8321) (8641.2214 6625.9542)
    ))
    ; P0699 -- see feature_dimensions_mm.csv
    ("02_CORNICES" 0 (
      (8702.2901 6625.9542) (8671.7557 6625.9542) (8641.2214 6625.9542)
    ))
    ; P0700 -- see feature_dimensions_mm.csv
    ("02_CORNICES" 0 (
      (8687.0229 8320.6107) (8687.0229 8137.4046) (8671.7557 8137.4046)
    ))
    ; P0701 -- see feature_dimensions_mm.csv
    ("02_CORNICES" 0 (
      (8854.9618 6625.9542) (8732.8244 6473.2824) (8671.7557 6473.2824)
    ))
    ; P0702 -- see feature_dimensions_mm.csv
    ("02_CORNICES" 0 (
      (8702.2901 6961.8321) (8732.8244 6961.8321)
    ))
    ; P0703 -- see feature_dimensions_mm.csv
    ("02_CORNICES" 0 (
      (8702.2901 6625.9542) (8702.2901 6961.8321)
    ))
    ; P0704 -- see feature_dimensions_mm.csv
    ("02_CORNICES" 0 (
      (8732.8244 6625.9542) (8702.2901 6625.9542)
    ))
    ; P0705 -- see feature_dimensions_mm.csv
    ("02_CORNICES" 0 (
      (8732.8244 6961.8321) (8793.8931 6961.8321)
    ))
    ; P0706 -- see feature_dimensions_mm.csv
    ("02_CORNICES" 0 (
      (8732.8244 6961.8321) (8732.8244 6625.9542)
    ))
    ; P0707 -- see feature_dimensions_mm.csv
    ("02_CORNICES" 0 (
      (8793.8931 6625.9542) (8732.8244 6625.9542)
    ))
    ; P0708 -- see feature_dimensions_mm.csv
    ("02_CORNICES" 0 (
      (8793.8931 6961.8321) (8824.4275 6961.8321)
    ))
    ; P0709 -- see feature_dimensions_mm.csv
    ("02_CORNICES" 0 (
      (8793.8931 6625.9542) (8793.8931 6961.8321)
    ))
    ; P0710 -- see feature_dimensions_mm.csv
    ("02_CORNICES" 0 (
      (8824.4275 6625.9542) (8793.8931 6625.9542)
    ))
    ; P0711 -- see feature_dimensions_mm.csv
    ("02_CORNICES" 0 (
      (8824.4275 6961.8321) (8854.9618 6961.8321) (8854.9618 6625.9542)
    ))
    ; P0712 -- see feature_dimensions_mm.csv
    ("02_CORNICES" 0 (
      (8824.4275 6961.8321) (8824.4275 6625.9542)
    ))
    ; P0713 -- see feature_dimensions_mm.csv
    ("02_CORNICES" 0 (
      (8854.9618 6625.9542) (8824.4275 6625.9542)
    ))
    ; P0714 -- see feature_dimensions_mm.csv
    ("02_CORNICES" 0 (
      (10122.1374 7923.6641) (10122.1374 8076.3359) (10345.4656 8076.3359) (10369.8321 7996.9466) (10394.1985 7996.9466)
      (10414.5038 7877.8626) (10467.2824 7877.8626) (10487.5878 7996.9466) (10507.8931 7996.9466) (10528.1985 8076.3359)
      (10751.5267 8076.3359) (10775.8931 7996.9466) (10800.2595 7996.9466) (10820.5649 7877.8626) (10873.3435 7877.8626)
      (10893.6489 7996.9466) (10913.9542 7996.9466) (10934.2595 8076.3359) (11157.5878 8076.3359) (11181.9542 7996.9466)
      (11206.3206 7996.9466) (11226.6107 7877.8626) (11279.4046 7877.8626) (11299.7099 7996.9466) (11320.0153 7996.9466)
      (11340.3206 8076.3359) (11563.6489 8076.3359) (11588.0153 7996.9466) (11612.3664 7996.9466) (11632.6718 7877.8626)
      (11685.4656 7877.8626) (11705.771 7996.9466) (11726.0763 7996.9466) (11746.3664 8076.3359) (11969.7099 8076.3359)
      (11994.0763 7996.9466) (12018.4275 7996.9466) (12038.7328 7877.8626) (12091.5267 7877.8626) (12111.8321 7996.9466)
      (12132.1221 7996.9466) (12152.4275 8076.3359) (12375.771 8076.3359) (12400.1221 7996.9466) (12424.4885 7996.9466)
      (12444.7939 7877.8626) (12497.5878 7877.8626) (12517.8779 7996.9466) (12538.1832 7996.9466) (12558.4885 8076.3359)
      (12781.8168 8076.3359) (12806.1832 7996.9466) (12830.5496 7996.9466) (12850.855 7877.8626) (12903.6336 7877.8626)
      (12923.9389 7996.9466) (12944.2443 7996.9466) (12964.5496 8076.3359) (13187.8779 8076.3359) (13212.2443 7996.9466)
      (13236.6107 7996.9466) (13256.916 7877.8626) (13309.6947 7877.8626) (13330.0 7996.9466) (13350.3053 7996.9466)
      (13370.6107 8076.3359) (13593.9389 8076.3359) (13618.3053 7996.9466) (13642.6718 7996.9466) (13662.9771 7877.8626)
      (13715.7557 7877.8626) (13736.0611 7996.9466) (13756.3664 7996.9466) (13776.6718 8076.3359) (14000.0 8076.3359)
      (14000.0 7740.458)
    ))
    ; P0715 -- see feature_dimensions_mm.csv
    ("02_CORNICES" 0 (
      (10357.8931 6656.4885) (10290.0763 6656.4885) (10274.8092 6656.4885)
    ))
    ; P0716 -- see feature_dimensions_mm.csv
    ("02_CORNICES" 0 (
      (10290.0763 6564.8855) (10274.8092 6564.8855) (10274.8092 6656.4885)
    ))
    ; P0717 -- see feature_dimensions_mm.csv
    ("02_CORNICES" 0 (
      (10274.8092 6656.4885) (10274.8092 6977.0992) (10290.0763 6977.0992) (10357.8931 6977.0992)
    ))
    ; P0718 -- see feature_dimensions_mm.csv
    ("02_CORNICES" 0 (
      (10717.5573 3679.3893) (10717.5573 3740.458) (10687.0229 3740.458) (10290.0763 3740.458) (10259.542 3740.458)
      (10259.542 3633.5878) (10274.8092 3633.5878)
    ))
    ; P0719 -- see feature_dimensions_mm.csv
    ("02_CORNICES" 0 (
      (10274.8092 3618.3206) (10335.8779 3618.3206)
    ))
    ; P0720 -- see feature_dimensions_mm.csv
    ("02_CORNICES" 0 (
      (10335.8779 3633.5878) (10290.0763 3633.5878)
    ))
    ; P0721 -- see feature_dimensions_mm.csv
    ("02_CORNICES" 0 (
      (10687.0229 3633.5878) (10335.8779 3633.5878)
    ))
    ; P0722 -- see feature_dimensions_mm.csv
    ("02_CORNICES" 0 (
      (10335.8779 3633.5878) (10335.8779 3618.3206)
    ))
    ; P0723 -- see feature_dimensions_mm.csv
    ("02_CORNICES" 0 (
      (10717.5573 3679.3893) (10687.0229 3679.3893) (10335.8779 3679.3893) (10335.8779 3664.1221) (10335.8779 3633.5878)
    ))
    ; P0724 -- see feature_dimensions_mm.csv
    ("02_CORNICES" 0 (
      (10335.8779 3618.3206) (10519.084 3618.3206)
    ))
    ; P0725 -- see feature_dimensions_mm.csv
    ("02_CORNICES" 0 (
      (10357.8931 6977.0992) (10440.9771 6977.0992)
    ))
    ; P0726 -- see feature_dimensions_mm.csv
    ("02_CORNICES" 0 (
      (10357.8931 6977.0992) (10357.8931 6656.4885)
    ))
    ; P0727 -- see feature_dimensions_mm.csv
    ("02_CORNICES" 0 (
      (10440.9771 6656.4885) (10357.8931 6656.4885)
    ))
    ; P0728 -- see feature_dimensions_mm.csv
    ("02_CORNICES" 0 (
      (10440.9771 6977.0992) (10524.0611 6977.0992)
    ))
    ; P0729 -- see feature_dimensions_mm.csv
    ("02_CORNICES" 0 (
      (10440.9771 6977.0992) (10440.9771 6656.4885)
    ))
    ; P0730 -- see feature_dimensions_mm.csv
    ("02_CORNICES" 0 (
      (10524.0611 6656.4885) (10440.9771 6656.4885)
    ))
    ; P0731 -- see feature_dimensions_mm.csv
    ("02_CORNICES" 0 (
      (10519.084 3618.3206) (13938.9313 3618.3206) (13938.9313 3633.5878)
    ))
    ; P0732 -- see feature_dimensions_mm.csv
    ("02_CORNICES" 0 (
      (10519.084 3618.3206) (10519.084 3389.313)
    ))
    ; P0733 -- see feature_dimensions_mm.csv
    ("02_CORNICES" 0 (
      (13961.8321 3389.313) (10519.084 3389.313)
    ))
    ; P0734 -- see feature_dimensions_mm.csv
    ("02_CORNICES" 0 (
      (10519.084 3389.313) (10519.084 3297.7099)
    ))
    ; P0735 -- see feature_dimensions_mm.csv
    ("02_CORNICES" 0 (
      (10519.084 3297.7099) (13893.1298 3297.7099) (13961.8321 3389.313)
    ))
    ; P0736 -- see feature_dimensions_mm.csv
    ("02_CORNICES" 0 (
      (10519.084 3297.7099) (10519.084 3282.4427) (13969.4656 3282.4427) (13969.4656 3389.313) (13961.8321 3389.313)
    ))
    ; P0737 -- see feature_dimensions_mm.csv
    ("02_CORNICES" 0 (
      (10524.0611 6977.0992) (10607.1298 6977.0992)
    ))
    ; P0738 -- see feature_dimensions_mm.csv
    ("02_CORNICES" 0 (
      (10524.0611 6977.0992) (10524.0611 6656.4885)
    ))
    ; P0739 -- see feature_dimensions_mm.csv
    ("02_CORNICES" 0 (
      (10607.1298 6656.4885) (10524.0611 6656.4885)
    ))
    ; P0740 -- see feature_dimensions_mm.csv
    ("02_CORNICES" 0 (
      (10564.8855 1969.4656) (10610.687 1862.5954) (10809.1603 1862.5954)
    ))
    ; P0741 -- see feature_dimensions_mm.csv
    ("02_CORNICES" 0 (
      (10607.1298 6977.0992) (10690.2137 6977.0992)
    ))
    ; P0742 -- see feature_dimensions_mm.csv
    ("02_CORNICES" 0 (
      (10607.1298 6977.0992) (10607.1298 6656.4885)
    ))
    ; P0743 -- see feature_dimensions_mm.csv
    ("02_CORNICES" 0 (
      (10690.2137 6656.4885) (10607.1298 6656.4885)
    ))
    ; P0744 -- see feature_dimensions_mm.csv
    ("02_CORNICES" 0 (
      (10690.2137 6977.0992) (10773.2977 6977.0992)
    ))
    ; P0745 -- see feature_dimensions_mm.csv
    ("02_CORNICES" 0 (
      (10690.2137 6977.0992) (10690.2137 6656.4885)
    ))
    ; P0746 -- see feature_dimensions_mm.csv
    ("02_CORNICES" 0 (
      (10773.2977 6656.4885) (10690.2137 6656.4885)
    ))
    ; P0747 -- see feature_dimensions_mm.csv
    ("02_CORNICES" 0 (
      (13404.5802 3679.3893) (13068.7023 3679.3893) (11053.4351 3679.3893) (10717.5573 3679.3893)
    ))
    ; P0748 -- see feature_dimensions_mm.csv
    ("02_CORNICES" 0 (
      (10717.5573 3633.5878) (10717.5573 3679.3893)
    ))
    ; P0749 -- see feature_dimensions_mm.csv
    ("02_CORNICES" 0 (
      (10773.2977 6977.0992) (10856.3817 6977.0992)
    ))
    ; P0750 -- see feature_dimensions_mm.csv
    ("02_CORNICES" 0 (
      (10773.2977 6977.0992) (10773.2977 6656.4885)
    ))
    ; P0751 -- see feature_dimensions_mm.csv
    ("02_CORNICES" 0 (
      (10856.3817 6656.4885) (10773.2977 6656.4885)
    ))
    ; P0752 -- see feature_dimensions_mm.csv
    ("02_CORNICES" 0 (
      (10856.3817 6977.0992) (10939.4656 6977.0992)
    ))
    ; P0753 -- see feature_dimensions_mm.csv
    ("02_CORNICES" 0 (
      (10856.3817 6977.0992) (10856.3817 6656.4885)
    ))
    ; P0754 -- see feature_dimensions_mm.csv
    ("02_CORNICES" 0 (
      (10939.4656 6656.4885) (10856.3817 6656.4885)
    ))
    ; P0755 -- see feature_dimensions_mm.csv
    ("02_CORNICES" 0 (
      (10939.4656 6977.0992) (11022.5496 6977.0992)
    ))
    ; P0756 -- see feature_dimensions_mm.csv
    ("02_CORNICES" 0 (
      (10939.4656 6977.0992) (10939.4656 6656.4885)
    ))
    ; P0757 -- see feature_dimensions_mm.csv
    ("02_CORNICES" 0 (
      (11022.5496 6656.4885) (10939.4656 6656.4885)
    ))
    ; P0758 -- see feature_dimensions_mm.csv
    ("02_CORNICES" 0 (
      (11022.5496 6977.0992) (11105.6336 6977.0992)
    ))
    ; P0759 -- see feature_dimensions_mm.csv
    ("02_CORNICES" 0 (
      (11022.5496 6977.0992) (11022.5496 6656.4885)
    ))
    ; P0760 -- see feature_dimensions_mm.csv
    ("02_CORNICES" 0 (
      (11105.6336 6656.4885) (11022.5496 6656.4885)
    ))
    ; P0761 -- see feature_dimensions_mm.csv
    ("02_CORNICES" 0 (
      (11105.6336 6977.0992) (11188.7023 6977.0992)
    ))
    ; P0762 -- see feature_dimensions_mm.csv
    ("02_CORNICES" 0 (
      (11105.6336 6977.0992) (11105.6336 6656.4885)
    ))
    ; P0763 -- see feature_dimensions_mm.csv
    ("02_CORNICES" 0 (
      (11188.7023 6656.4885) (11105.6336 6656.4885)
    ))
    ; P0764 -- see feature_dimensions_mm.csv
    ("02_CORNICES" 0 (
      (11188.7023 6977.0992) (11271.7863 6977.0992)
    ))
    ; P0765 -- see feature_dimensions_mm.csv
    ("02_CORNICES" 0 (
      (11188.7023 6977.0992) (11188.7023 6656.4885)
    ))
    ; P0766 -- see feature_dimensions_mm.csv
    ("02_CORNICES" 0 (
      (11271.7863 6656.4885) (11188.7023 6656.4885)
    ))
    ; P0767 -- see feature_dimensions_mm.csv
    ("02_CORNICES" 0 (
      (11261.4962 2373.2977) (11249.4351 2433.2366) (11213.7405 2610.687) (11503.8168 2610.687) (11468.1221 2433.2366)
      (11456.0611 2373.2977)
    ))
    ; P0768 -- see feature_dimensions_mm.csv
    ("02_CORNICES" 0 (
      (11451.6031 2351.145) (11265.9542 2351.145)
    ))
    ; P0769 -- see feature_dimensions_mm.csv
    ("02_CORNICES" 0 (
      (11271.7863 6977.0992) (11354.8702 6977.0992)
    ))
    ; P0770 -- see feature_dimensions_mm.csv
    ("02_CORNICES" 0 (
      (11271.7863 6977.0992) (11271.7863 6656.4885)
    ))
    ; P0771 -- see feature_dimensions_mm.csv
    ("02_CORNICES" 0 (
      (11354.8702 6656.4885) (11271.7863 6656.4885)
    ))
    ; P0772 -- see feature_dimensions_mm.csv
    ("02_CORNICES" 0 (
      (11354.8702 6977.0992) (11437.9542 6977.0992)
    ))
    ; P0773 -- see feature_dimensions_mm.csv
    ("02_CORNICES" 0 (
      (11354.8702 6977.0992) (11354.8702 6656.4885)
    ))
    ; P0774 -- see feature_dimensions_mm.csv
    ("02_CORNICES" 0 (
      (11437.9542 6656.4885) (11354.8702 6656.4885)
    ))
    ; P0775 -- see feature_dimensions_mm.csv
    ("02_CORNICES" 0 (
      (11437.9542 6977.0992) (11521.0382 6977.0992)
    ))
    ; P0776 -- see feature_dimensions_mm.csv
    ("02_CORNICES" 0 (
      (11437.9542 6977.0992) (11437.9542 6656.4885)
    ))
    ; P0777 -- see feature_dimensions_mm.csv
    ("02_CORNICES" 0 (
      (11521.0382 6656.4885) (11437.9542 6656.4885)
    ))
    ; P0778 -- see feature_dimensions_mm.csv
    ("02_CORNICES" 0 (
      (11521.0382 6977.0992) (11604.1221 6977.0992)
    ))
    ; P0779 -- see feature_dimensions_mm.csv
    ("02_CORNICES" 0 (
      (11521.0382 6977.0992) (11521.0382 6656.4885)
    ))
    ; P0780 -- see feature_dimensions_mm.csv
    ("02_CORNICES" 0 (
      (11604.1221 6656.4885) (11521.0382 6656.4885)
    ))
    ; P0781 -- see feature_dimensions_mm.csv
    ("02_CORNICES" 0 (
      (11604.1221 6977.0992) (11687.2061 6977.0992)
    ))
    ; P0782 -- see feature_dimensions_mm.csv
    ("02_CORNICES" 0 (
      (11604.1221 6977.0992) (11604.1221 6656.4885)
    ))
    ; P0783 -- see feature_dimensions_mm.csv
    ("02_CORNICES" 0 (
      (11687.2061 6656.4885) (11604.1221 6656.4885)
    ))
    ; P0784 -- see feature_dimensions_mm.csv
    ("02_CORNICES" 0 (
      (11687.2061 6977.0992) (11770.2748 6977.0992)
    ))
    ; P0785 -- see feature_dimensions_mm.csv
    ("02_CORNICES" 0 (
      (11687.2061 6977.0992) (11687.2061 6656.4885)
    ))
    ; P0786 -- see feature_dimensions_mm.csv
    ("02_CORNICES" 0 (
      (11770.2748 6656.4885) (11687.2061 6656.4885)
    ))
    ; P0787 -- see feature_dimensions_mm.csv
    ("02_CORNICES" 0 (
      (11770.2748 6977.0992) (11853.3588 6977.0992)
    ))
    ; P0788 -- see feature_dimensions_mm.csv
    ("02_CORNICES" 0 (
      (11770.2748 6977.0992) (11770.2748 6656.4885)
    ))
    ; P0789 -- see feature_dimensions_mm.csv
    ("02_CORNICES" 0 (
      (11853.3588 6656.4885) (11770.2748 6656.4885)
    ))
    ; P0790 -- see feature_dimensions_mm.csv
    ("02_CORNICES" 0 (
      (11853.3588 6977.0992) (11936.4427 6977.0992)
    ))
    ; P0791 -- see feature_dimensions_mm.csv
    ("02_CORNICES" 0 (
      (11853.3588 6977.0992) (11853.3588 6656.4885)
    ))
    ; P0792 -- see feature_dimensions_mm.csv
    ("02_CORNICES" 0 (
      (11936.4427 6656.4885) (11853.3588 6656.4885)
    ))
    ; P0793 -- see feature_dimensions_mm.csv
    ("02_CORNICES" 0 (
      (12014.9924 5938.9313) (11908.3969 5938.9313) (11924.1832 5864.4122)
    ))
    ; P0794 -- see feature_dimensions_mm.csv
    ("02_CORNICES" 0 (
      (11931.9237 5827.8321) (11941.4198 5782.9924) (11963.3588 5679.3893)
    ))
    ; P0795 -- see feature_dimensions_mm.csv
    ("02_CORNICES" 0 (
      (11954.1985 1969.4656) (11877.6336 2035.0992) (11847.3282 2061.0687) (11867.2366 2061.0687) (11933.9084 2061.0687)
    ))
    ; P0796 -- see feature_dimensions_mm.csv
    ("02_CORNICES" 0 (
      (11936.4427 6977.0992) (12019.5267 6977.0992)
    ))
    ; P0797 -- see feature_dimensions_mm.csv
    ("02_CORNICES" 0 (
      (11936.4427 6977.0992) (11936.4427 6656.4885)
    ))
    ; P0798 -- see feature_dimensions_mm.csv
    ("02_CORNICES" 0 (
      (12019.5267 6656.4885) (11936.4427 6656.4885)
    ))
    ; P0799 -- see feature_dimensions_mm.csv
    ("02_CORNICES" 0 (
      (12019.5267 6977.0992) (12102.6107 6977.0992)
    ))
    ; P0800 -- see feature_dimensions_mm.csv
    ("02_CORNICES" 0 (
      (12019.5267 6977.0992) (12019.5267 6656.4885)
    ))
    ; P0801 -- see feature_dimensions_mm.csv
    ("02_CORNICES" 0 (
      (12102.6107 6656.4885) (12019.5267 6656.4885)
    ))
    ; P0802 -- see feature_dimensions_mm.csv
    ("02_CORNICES" 0 (
      (12102.6107 6977.0992) (12185.6947 6977.0992)
    ))
    ; P0803 -- see feature_dimensions_mm.csv
    ("02_CORNICES" 0 (
      (12102.6107 6977.0992) (12102.6107 6656.4885)
    ))
    ; P0804 -- see feature_dimensions_mm.csv
    ("02_CORNICES" 0 (
      (12185.6947 6656.4885) (12102.6107 6656.4885)
    ))
    ; P0805 -- see feature_dimensions_mm.csv
    ("02_CORNICES" 0 (
      (12192.2901 5837.6641) (12213.7405 5938.9313) (12139.8015 5938.9313)
    ))
    ; P0806 -- see feature_dimensions_mm.csv
    ("02_CORNICES" 0 (
      (12158.7786 5679.3893) (12180.7176 5782.9924) (12190.2137 5827.8321)
    ))
    ; P0807 -- see feature_dimensions_mm.csv
    ("02_CORNICES" 0 (
      (12185.6947 6977.0992) (12268.7786 6977.0992)
    ))
    ; P0808 -- see feature_dimensions_mm.csv
    ("02_CORNICES" 0 (
      (12185.6947 6977.0992) (12185.6947 6656.4885)
    ))
    ; P0809 -- see feature_dimensions_mm.csv
    ("02_CORNICES" 0 (
      (12268.7786 6656.4885) (12185.6947 6656.4885)
    ))
    ; P0810 -- see feature_dimensions_mm.csv
    ("02_CORNICES" 0 (
      (12268.7786 6977.0992) (12351.8626 6977.0992)
    ))
    ; P0811 -- see feature_dimensions_mm.csv
    ("02_CORNICES" 0 (
      (12268.7786 6977.0992) (12268.7786 6656.4885)
    ))
    ; P0812 -- see feature_dimensions_mm.csv
    ("02_CORNICES" 0 (
      (12351.8626 6656.4885) (12268.7786 6656.4885)
    ))
    ; P0813 -- see feature_dimensions_mm.csv
    ("02_CORNICES" 0 (
      (12351.8626 6977.0992) (12434.9313 6977.0992)
    ))
    ; P0814 -- see feature_dimensions_mm.csv
    ("02_CORNICES" 0 (
      (12351.8626 6977.0992) (12351.8626 6656.4885)
    ))
    ; P0815 -- see feature_dimensions_mm.csv
    ("02_CORNICES" 0 (
      (12434.9313 6656.4885) (12351.8626 6656.4885)
    ))
    ; P0816 -- see feature_dimensions_mm.csv
    ("02_CORNICES" 0 (
      (12434.9313 6977.0992) (12518.0153 6977.0992)
    ))
    ; P0817 -- see feature_dimensions_mm.csv
    ("02_CORNICES" 0 (
      (12434.9313 6977.0992) (12434.9313 6656.4885)
    ))
    ; P0818 -- see feature_dimensions_mm.csv
    ("02_CORNICES" 0 (
      (12518.0153 6656.4885) (12434.9313 6656.4885)
    ))
    ; P0819 -- see feature_dimensions_mm.csv
    ("02_CORNICES" 0 (
      (12518.0153 6977.0992) (12601.0992 6977.0992)
    ))
    ; P0820 -- see feature_dimensions_mm.csv
    ("02_CORNICES" 0 (
      (12518.0153 6977.0992) (12518.0153 6656.4885)
    ))
    ; P0821 -- see feature_dimensions_mm.csv
    ("02_CORNICES" 0 (
      (12601.0992 6656.4885) (12518.0153 6656.4885)
    ))
    ; P0822 -- see feature_dimensions_mm.csv
    ("02_CORNICES" 0 (
      (12601.0992 6977.0992) (12684.1832 6977.0992)
    ))
    ; P0823 -- see feature_dimensions_mm.csv
    ("02_CORNICES" 0 (
      (12601.0992 6977.0992) (12601.0992 6656.4885)
    ))
    ; P0824 -- see feature_dimensions_mm.csv
    ("02_CORNICES" 0 (
      (12684.1832 6656.4885) (12601.0992 6656.4885)
    ))
    ; P0825 -- see feature_dimensions_mm.csv
    ("02_CORNICES" 0 (
      (12605.0076 2373.2977) (12592.9466 2433.2366) (12557.2519 2610.687) (12847.3282 2610.687) (12811.6336 2433.2366)
      (12799.5725 2373.2977)
    ))
    ; P0826 -- see feature_dimensions_mm.csv
    ("02_CORNICES" 0 (
      (12684.1832 6977.0992) (12767.2672 6977.0992)
    ))
    ; P0827 -- see feature_dimensions_mm.csv
    ("02_CORNICES" 0 (
      (12684.1832 6977.0992) (12684.1832 6656.4885)
    ))
    ; P0828 -- see feature_dimensions_mm.csv
    ("02_CORNICES" 0 (
      (12767.2672 6656.4885) (12684.1832 6656.4885)
    ))
    ; P0829 -- see feature_dimensions_mm.csv
    ("02_CORNICES" 0 (
      (12767.2672 6977.0992) (12850.3511 6977.0992)
    ))
    ; P0830 -- see feature_dimensions_mm.csv
    ("02_CORNICES" 0 (
      (12767.2672 6977.0992) (12767.2672 6656.4885)
    ))
    ; P0831 -- see feature_dimensions_mm.csv
    ("02_CORNICES" 0 (
      (12850.3511 6656.4885) (12767.2672 6656.4885)
    ))
    ; P0832 -- see feature_dimensions_mm.csv
    ("02_CORNICES" 0 (
      (12850.3511 6977.0992) (12933.4351 6977.0992)
    ))
    ; P0833 -- see feature_dimensions_mm.csv
    ("02_CORNICES" 0 (
      (12850.3511 6977.0992) (12850.3511 6656.4885)
    ))
    ; P0834 -- see feature_dimensions_mm.csv
    ("02_CORNICES" 0 (
      (12933.4351 6656.4885) (12850.3511 6656.4885)
    ))
    ; P0835 -- see feature_dimensions_mm.csv
    ("02_CORNICES" 0 (
      (12933.4351 6977.0992) (13016.5038 6977.0992)
    ))
    ; P0836 -- see feature_dimensions_mm.csv
    ("02_CORNICES" 0 (
      (12933.4351 6977.0992) (12933.4351 6656.4885)
    ))
    ; P0837 -- see feature_dimensions_mm.csv
    ("02_CORNICES" 0 (
      (13016.5038 6656.4885) (12933.4351 6656.4885)
    ))
    ; P0838 -- see feature_dimensions_mm.csv
    ("02_CORNICES" 0 (
      (13016.5038 6977.0992) (13099.5878 6977.0992)
    ))
    ; P0839 -- see feature_dimensions_mm.csv
    ("02_CORNICES" 0 (
      (13016.5038 6977.0992) (13016.5038 6656.4885)
    ))
    ; P0840 -- see feature_dimensions_mm.csv
    ("02_CORNICES" 0 (
      (13099.5878 6656.4885) (13016.5038 6656.4885)
    ))
    ; P0841 -- see feature_dimensions_mm.csv
    ("02_CORNICES" 0 (
      (13099.5878 6977.0992) (13182.6718 6977.0992)
    ))
    ; P0842 -- see feature_dimensions_mm.csv
    ("02_CORNICES" 0 (
      (13099.5878 6977.0992) (13099.5878 6656.4885)
    ))
    ; P0843 -- see feature_dimensions_mm.csv
    ("02_CORNICES" 0 (
      (13182.6718 6656.4885) (13099.5878 6656.4885)
    ))
    ; P0844 -- see feature_dimensions_mm.csv
    ("02_CORNICES" 0 (
      (13182.6718 6977.0992) (13265.7557 6977.0992)
    ))
    ; P0845 -- see feature_dimensions_mm.csv
    ("02_CORNICES" 0 (
      (13182.6718 6977.0992) (13182.6718 6656.4885)
    ))
    ; P0846 -- see feature_dimensions_mm.csv
    ("02_CORNICES" 0 (
      (13265.7557 6656.4885) (13182.6718 6656.4885)
    ))
    ; P0847 -- see feature_dimensions_mm.csv
    ("02_CORNICES" 0 (
      (13265.7557 6977.0992) (13348.8397 6977.0992)
    ))
    ; P0848 -- see feature_dimensions_mm.csv
    ("02_CORNICES" 0 (
      (13265.7557 6977.0992) (13265.7557 6656.4885)
    ))
    ; P0849 -- see feature_dimensions_mm.csv
    ("02_CORNICES" 0 (
      (13348.8397 6656.4885) (13265.7557 6656.4885)
    ))
    ; P0850 -- see feature_dimensions_mm.csv
    ("02_CORNICES" 0 (
      (13389.313 1862.5954) (13343.5115 1969.4656)
    ))
    ; P0851 -- see feature_dimensions_mm.csv
    ("02_CORNICES" 0 (
      (13348.8397 6977.0992) (13431.9237 6977.0992)
    ))
    ; P0852 -- see feature_dimensions_mm.csv
    ("02_CORNICES" 0 (
      (13348.8397 6977.0992) (13348.8397 6656.4885)
    ))
    ; P0853 -- see feature_dimensions_mm.csv
    ("02_CORNICES" 0 (
      (13431.9237 6656.4885) (13348.8397 6656.4885)
    ))
    ; P0854 -- see feature_dimensions_mm.csv
    ("02_CORNICES" 0 (
      (13862.5954 3679.3893) (13435.1145 3679.3893) (13404.5802 3679.3893)
    ))
    ; P0855 -- see feature_dimensions_mm.csv
    ("02_CORNICES" 0 (
      (13862.5954 3633.5878) (13832.0611 3633.5878) (13435.1145 3633.5878) (13404.5802 3633.5878) (13404.5802 3679.3893)
    ))
    ; P0856 -- see feature_dimensions_mm.csv
    ("02_CORNICES" 0 (
      (13862.5954 3679.3893) (13862.5954 3740.458) (13832.0611 3740.458) (13435.1145 3740.458) (13404.5802 3740.458)
      (13404.5802 3679.3893)
    ))
    ; P0857 -- see feature_dimensions_mm.csv
    ("02_CORNICES" 0 (
      (13431.9237 6977.0992) (13515.0076 6977.0992)
    ))
    ; P0858 -- see feature_dimensions_mm.csv
    ("02_CORNICES" 0 (
      (13431.9237 6977.0992) (13431.9237 6656.4885)
    ))
    ; P0859 -- see feature_dimensions_mm.csv
    ("02_CORNICES" 0 (
      (13515.0076 6656.4885) (13431.9237 6656.4885)
    ))
    ; P0860 -- see feature_dimensions_mm.csv
    ("02_CORNICES" 0 (
      (13515.0076 6977.0992) (13598.0763 6977.0992)
    ))
    ; P0861 -- see feature_dimensions_mm.csv
    ("02_CORNICES" 0 (
      (13515.0076 6977.0992) (13515.0076 6656.4885)
    ))
    ; P0862 -- see feature_dimensions_mm.csv
    ("02_CORNICES" 0 (
      (13598.0763 6656.4885) (13515.0076 6656.4885)
    ))
    ; P0863 -- see feature_dimensions_mm.csv
    ("02_CORNICES" 0 (
      (13598.0763 6977.0992) (13681.1603 6977.0992)
    ))
    ; P0864 -- see feature_dimensions_mm.csv
    ("02_CORNICES" 0 (
      (13598.0763 6977.0992) (13598.0763 6656.4885)
    ))
    ; P0865 -- see feature_dimensions_mm.csv
    ("02_CORNICES" 0 (
      (13681.1603 6656.4885) (13598.0763 6656.4885)
    ))
    ; P0866 -- see feature_dimensions_mm.csv
    ("02_CORNICES" 0 (
      (13681.1603 6977.0992) (13764.2443 6977.0992)
    ))
    ; P0867 -- see feature_dimensions_mm.csv
    ("02_CORNICES" 0 (
      (13681.1603 6977.0992) (13681.1603 6656.4885)
    ))
    ; P0868 -- see feature_dimensions_mm.csv
    ("02_CORNICES" 0 (
      (13764.2443 6656.4885) (13681.1603 6656.4885)
    ))
    ; P0869 -- see feature_dimensions_mm.csv
    ("02_CORNICES" 0 (
      (13764.2443 6977.0992) (13832.0611 6977.0992) (13847.3282 6977.0992) (13847.3282 6656.4885)
    ))
    ; P0870 -- see feature_dimensions_mm.csv
    ("02_CORNICES" 0 (
      (13764.2443 6977.0992) (13764.2443 6656.4885)
    ))
    ; P0871 -- see feature_dimensions_mm.csv
    ("02_CORNICES" 0 (
      (13847.3282 6656.4885) (13832.0611 6656.4885) (13764.2443 6656.4885)
    ))
    ; P0872 -- see feature_dimensions_mm.csv
    ("02_CORNICES" 0 (
      (13847.3282 6656.4885) (13847.3282 6564.8855) (13832.0611 6564.8855)
    ))
    ; P0873 -- see feature_dimensions_mm.csv
    ("02_CORNICES" 0 (
      (13938.9313 3633.5878) (13938.9313 3679.3893) (13862.5954 3679.3893)
    ))
    ; P0874 -- see feature_dimensions_mm.csv
    ("02_CORNICES" 0 (
      (13862.5954 3633.5878) (13862.5954 3679.3893)
    ))
    ; P0875 -- see feature_dimensions_mm.csv
    ("02_CORNICES" 0 (
      (13938.9313 3633.5878) (13862.5954 3633.5878)
    ))
    ; P0876 -- see feature_dimensions_mm.csv
    ("02_CORNICES" 0 (
      (13961.8321 3389.313) (13984.7328 3419.8473) (14000.0 3633.5878) (13938.9313 3633.5878)
    ))
    ; P0877 -- see feature_dimensions_mm.csv
    ("02_CORNICES" 1 (
      (14000.0 7740.458) (13877.8626 7557.2519) (10244.2748 7557.2519) (10122.1374 7740.458)
    ))
    ; P0878 -- see feature_dimensions_mm.csv
    ("02_CORNICES" 1 (
      (2151.7863 2580.1527) (2191.7252 2381.6794) (2327.3588 2381.6794) (2367.2977 2580.1527)
    ))
    ; P0879 -- see feature_dimensions_mm.csv
    ("02_CORNICES" 1 (
      (2862.1069 5908.3969) (2904.1374 5709.9237) (3050.0611 5709.9237) (3092.0916 5908.3969)
    ))
    ; P0880 -- see feature_dimensions_mm.csv
    ("02_CORNICES" 1 (
      (3579.7405 2595.4198) (3618.9008 2412.2137) (3755.145 2412.2137) (3794.3053 2595.4198)
    ))
    ; P0881 -- see feature_dimensions_mm.csv
    ("02_CORNICES" 1 (
      (9395.6794 2610.687) (9433.5115 2412.2137) (9558.855 2412.2137) (9596.687 2610.687)
    ))
    ; P0882 -- see feature_dimensions_mm.csv
    ("02_CORNICES" 1 (
      (11251.0229 2580.1527) (11290.9618 2381.6794) (11426.5954 2381.6794) (11466.5344 2580.1527)
    ))
    ; P0883 -- see feature_dimensions_mm.csv
    ("02_CORNICES" 1 (
      (11946.0763 5908.3969) (11988.1069 5709.9237) (12134.0305 5709.9237) (12176.0611 5908.3969)
    ))
    ; P0884 -- see feature_dimensions_mm.csv
    ("02_CORNICES" 1 (
      (12594.5344 2580.1527) (12634.4733 2381.6794) (12770.1069 2381.6794) (12810.0458 2580.1527)
    ))
    ; P0885 -- see feature_dimensions_mm.csv
    ("03_FRAMES_DOORS" 0 (
      (1404.5802 9145.0382) (1404.5802 8946.5649) (1206.1069 8946.5649) (1206.1069 9145.0382)
    ))
    ; P0886 -- see feature_dimensions_mm.csv
    ("03_FRAMES_DOORS" 0 (
      (1435.1145 656.4885) (1709.9237 656.4885)
    ))
    ; P0887 -- see feature_dimensions_mm.csv
    ("03_FRAMES_DOORS" 0 (
      (1664.1221 1862.5954) (1709.9237 1862.5954)
    ))
    ; P0888 -- see feature_dimensions_mm.csv
    ("03_FRAMES_DOORS" 0 (
      (1695.3435 2088.3817) (1684.4122 2061.0687)
    ))
    ; P0889 -- see feature_dimensions_mm.csv
    ("03_FRAMES_DOORS" 0 (
      (1709.9237 1862.5954) (1709.9237 656.4885)
    ))
    ; P0890 -- see feature_dimensions_mm.csv
    ("03_FRAMES_DOORS" 0 (
      (2166.7176 2351.145) (2162.2595 2373.2977) (2152.3206 2371.7557) (2117.2977 2364.0763) (2082.8702 2354.2595)
      (2049.2061 2342.3511) (2016.458 2328.3969) (1984.7328 2312.458) (1954.1832 2294.6107) (1924.9618 2274.916)
      (1897.1603 2253.4656) (1870.9008 2230.3511) (1846.3206 2205.6794) (1823.4962 2179.542) (1802.5496 2152.0611)
      (1783.5573 2123.3588) (1766.6107 2093.542) (1751.7557 2062.7481) (1739.0992 2031.1145) (1728.6565 1998.7481)
      (1720.4885 1965.8321) (1714.626 1932.4733) (1711.0992 1898.8244) (1709.9237 1865.0382) (1709.9237 1862.5954)
    ))
    ; P0891 -- see feature_dimensions_mm.csv
    ("03_FRAMES_DOORS" 0 (
      (1709.9237 656.4885) (1770.9924 656.4885)
    ))
    ; P0892 -- see feature_dimensions_mm.csv
    ("03_FRAMES_DOORS" 0 (
      (1751.771 2187.6183) (1730.6718 2155.7252)
    ))
    ; P0893 -- see feature_dimensions_mm.csv
    ("03_FRAMES_DOORS" 0 (
      (1770.9924 656.4885) (2748.0916 656.4885)
    ))
    ; P0894 -- see feature_dimensions_mm.csv
    ("03_FRAMES_DOORS" 0 (
      (1770.9924 656.4885) (1770.9924 1861.374) (1772.0458 1891.4046) (1775.1756 1921.313) (1780.3817 1950.9618)
      (1787.6336 1980.229) (1796.916 2008.9924) (1808.1832 2037.1145) (1821.374 2064.4885) (1836.4427 2090.9924)
      (1853.3282 2116.5191) (1871.9542 2140.9466) (1892.229 2164.1679) (1914.0916 2186.1069) (1937.4198 2206.6412)
      (1962.1374 2225.7099) (1988.1221 2243.2214) (2015.2672 2259.084) (2043.4656 2273.2519) (2072.5802 2285.6489)
      (2102.5038 2296.2443) (2133.0992 2304.9618) (2164.229 2311.7863) (2195.771 2316.687) (2227.5878 2319.6336)
      (2259.542 2320.6107) (2291.4962 2319.6336) (2323.313 2316.687) (2354.855 2311.7863) (2385.9847 2304.9618)
      (2416.5802 2296.2443) (2446.5038 2285.6489) (2475.6183 2273.2519) (2503.8168 2259.084) (2530.9618 2243.2214)
      (2556.9466 2225.7099) (2581.6641 2206.6412) (2604.9924 2186.1069) (2626.855 2164.1679) (2647.1298 2140.9466)
      (2665.7557 2116.5191) (2682.6412 2090.9924) (2697.7099 2064.4885) (2710.9008 2037.1145) (2722.1679 2008.9924)
      (2731.4504 1980.229) (2738.7023 1950.9618) (2743.9084 1921.313) (2747.0382 1891.4046) (2748.0916 1861.374)
      (2748.0916 656.4885)
    ))
    ; P0895 -- see feature_dimensions_mm.csv
    ("03_FRAMES_DOORS" 0 (
      (1920.2595 2346.0) (1887.7863 2324.1221)
    ))
    ; P0896 -- see feature_dimensions_mm.csv
    ("03_FRAMES_DOORS" 0 (
      (1989.4351 2383.542) (1954.1985 2365.8473)
    ))
    ; P0897 -- see feature_dimensions_mm.csv
    ("03_FRAMES_DOORS" 0 (
      (2045.8015 4412.2137) (2045.8015 3832.0611)
    ))
    ; P0898 -- see feature_dimensions_mm.csv
    ("03_FRAMES_DOORS" 0 (
      (2152.6718 4473.2824) (2259.542 4473.2824)
    ))
    ; P0899 -- see feature_dimensions_mm.csv
    ("03_FRAMES_DOORS" 0 (
      (2857.4504 5782.9924) (2817.5725 5775.8015) (2770.5344 5766.6412) (2721.5725 5756.3664) (2671.1603 5744.9924)
      (2619.7557 5732.5038) (2567.8321 5718.8702) (2515.8626 5704.1069) (2464.3206 5688.1985) (2413.6641 5671.145)
      (2364.3664 5652.9313) (2316.8855 5633.5573) (2271.7099 5613.0076) (2229.2977 5591.2672) (2190.1221 5568.3511)
      (2154.6412 5544.229) (2123.3435 5518.916) (2096.6718 5492.3969) (2075.1298 5464.6565) (2059.145 5435.6794)
      (2049.2214 5405.4809) (2045.8015 5374.0458) (2045.8015 4473.2824) (2152.6718 4473.2824)
    ))
    ; P0900 -- see feature_dimensions_mm.csv
    ("03_FRAMES_DOORS" 0 (
      (2885.1298 5679.3893) (2875.4046 5677.6183) (2835.8779 5669.8473) (2794.2443 5661.0076) (2750.9008 5651.1145)
      (2706.2595 5640.1374) (2660.7634 5628.0916) (2614.8092 5614.9466) (2568.7939 5600.7176) (2523.1603 5585.374)
      (2478.3206 5568.9313) (2434.6718 5551.374) (2392.6565 5532.687) (2352.6565 5512.8702) (2315.1145 5491.9084)
      (2280.4275 5469.8015) (2249.0229 5446.5496) (2221.313 5422.1374) (2197.7099 5396.5649) (2178.626 5369.8168)
      (2164.4885 5341.8779) (2155.6947 5312.7634) (2152.6718 5282.4427) (2152.6718 4473.2824)
    ))
    ; P0901 -- see feature_dimensions_mm.csv
    ("03_FRAMES_DOORS" 0 (
      (2152.6718 4412.2137) (2152.6718 3832.0611)
    ))
    ; P0902 -- see feature_dimensions_mm.csv
    ("03_FRAMES_DOORS" 0 (
      (2259.542 4473.2824) (2398.5344 4473.2824) (2432.0 4473.2824) (2554.2595 4473.2824) (2587.7252 4473.2824)
      (2709.9847 4473.2824) (2743.4504 4473.2824) (2865.7099 4473.2824) (2899.1756 4473.2824) (2938.9313 4473.2824)
    ))
    ; P0903 -- see feature_dimensions_mm.csv
    ("03_FRAMES_DOORS" 0 (
      (2621.7252 5489.0229) (2603.4504 5482.7481) (2582.0153 5475.3893) (2542.9771 5460.7634) (2504.9924 5445.145)
      (2468.4122 5428.5344) (2433.6031 5410.9313) (2400.9313 5392.3053) (2370.7481 5372.6565) (2343.4046 5351.9847)
      (2319.2824 5330.2901) (2298.7481 5307.542) (2282.1374 5283.771) (2269.8168 5258.9466) (2262.1679 5233.0534)
      (2259.542 5206.1069) (2259.542 4473.2824)
    ))
    ; P0904 -- see feature_dimensions_mm.csv
    ("03_FRAMES_DOORS" 0 (
      (2388.4427 4412.2137) (2259.542 4412.2137)
    ))
    ; P0905 -- see feature_dimensions_mm.csv
    ("03_FRAMES_DOORS" 0 (
      (2809.1603 656.4885) (2809.1603 1865.0382) (2807.9847 1898.8244) (2804.458 1932.4733) (2798.5954 1965.8321)
      (2790.4275 1998.7481) (2779.9847 2031.1145) (2767.3282 2062.7481) (2752.4733 2093.542) (2735.5267 2123.3588)
      (2716.5344 2152.0611) (2695.5878 2179.542) (2672.7634 2205.6794) (2648.1832 2230.3511) (2621.9237 2253.4656)
      (2594.1221 2274.916) (2564.9008 2294.6107) (2534.3511 2312.458) (2502.626 2328.3969) (2469.8779 2342.3511)
      (2436.2137 2354.2595) (2401.7863 2364.0763) (2366.7634 2371.7557) (2356.8244 2373.2977) (2352.3664 2351.145)
    ))
    ; P0906 -- see feature_dimensions_mm.csv
    ("03_FRAMES_DOORS" 0 (
      (2417.6031 2423.1908) (2378.687 2431.7252) (2368.8855 2433.2366)
    ))
    ; P0907 -- see feature_dimensions_mm.csv
    ("03_FRAMES_DOORS" 0 (
      (2544.1679 4412.2137) (2442.0916 4412.2137)
    ))
    ; P0908 -- see feature_dimensions_mm.csv
    ("03_FRAMES_DOORS" 0 (
      (2699.8931 4412.2137) (2597.8168 4412.2137)
    ))
    ; P0909 -- see feature_dimensions_mm.csv
    ("03_FRAMES_DOORS" 0 (
      (3235.9847 5517.8015) (3212.8244 5524.0611) (3173.9847 5533.8168) (3136.2595 5542.6107) (3100.0153 5550.4733)
      (3065.6183 5557.374) (3033.4198 5563.3435) (3003.8015 5568.3969) (2977.0992 5572.5191) (2950.3969 5568.3969)
      (2920.7786 5563.3435) (2888.5802 5557.374) (2854.1832 5550.4733) (2817.9389 5542.6107) (2780.2137 5533.8168)
      (2741.374 5524.0611) (2701.771 5513.3435) (2679.0687 5506.7176) (2661.771 5501.6641)
    ))
    ; P0910 -- see feature_dimensions_mm.csv
    ("03_FRAMES_DOORS" 0 (
      (2748.0916 656.4885) (2809.1603 656.4885)
    ))
    ; P0911 -- see feature_dimensions_mm.csv
    ("03_FRAMES_DOORS" 0 (
      (2938.9313 4412.2137) (2909.2672 4412.2137) (2855.6183 4412.2137) (2753.542 4412.2137)
    ))
    ; P0912 -- see feature_dimensions_mm.csv
    ("03_FRAMES_DOORS" 0 (
      (2854.7481 1995.8321) (2778.626 2061.0687)
    ))
    ; P0913 -- see feature_dimensions_mm.csv
    ("03_FRAMES_DOORS" 0 (
      (2807.2519 2122.5954) (2788.4122 2155.7252)
    ))
    ; P0914 -- see feature_dimensions_mm.csv
    ("03_FRAMES_DOORS" 0 (
      (2809.1603 656.4885) (2824.4275 656.4885)
    ))
    ; P0915 -- see feature_dimensions_mm.csv
    ("03_FRAMES_DOORS" 0 (
      (2824.4275 656.4885) (3129.771 656.4885) (3129.771 931.2977) (3129.771 1282.4427)
    ))
    ; P0916 -- see feature_dimensions_mm.csv
    ("03_FRAMES_DOORS" 0 (
      (2824.4275 656.4885) (2824.4275 1862.5954) (2870.229 1862.5954)
    ))
    ; P0917 -- see feature_dimensions_mm.csv
    ("03_FRAMES_DOORS" 0 (
      (2858.4885 1980.687) (2857.4962 1984.7328)
    ))
    ; P0918 -- see feature_dimensions_mm.csv
    ("03_FRAMES_DOORS" 0 (
      (2870.229 1868.7023) (2868.916 1906.2443)
    ))
    ; P0919 -- see feature_dimensions_mm.csv
    ("03_FRAMES_DOORS" 0 (
      (2879.3893 5679.3893) (2885.1298 5679.3893)
    ))
    ; P0920 -- see feature_dimensions_mm.csv
    ("03_FRAMES_DOORS" 0 (
      (2885.1298 5679.3893) (3069.0687 5679.3893)
    ))
    ; P0921 -- see feature_dimensions_mm.csv
    ("03_FRAMES_DOORS" 0 (
      (2938.9313 4473.2824) (3015.2672 4473.2824)
    ))
    ; P0922 -- see feature_dimensions_mm.csv
    ("03_FRAMES_DOORS" 0 (
      (3015.2672 4473.2824) (3015.2672 5557.2519) (2938.9313 5557.2519) (2938.9313 4473.2824)
    ))
    ; P0923 -- see feature_dimensions_mm.csv
    ("03_FRAMES_DOORS" 0 (
      (2961.8321 4412.2137) (2938.9313 4412.2137)
    ))
    ; P0924 -- see feature_dimensions_mm.csv
    ("03_FRAMES_DOORS" 0 (
      (2938.9313 4412.2137) (2938.9313 3832.0611)
    ))
    ; P0925 -- see feature_dimensions_mm.csv
    ("03_FRAMES_DOORS" 0 (
      (3015.2672 4412.2137) (2992.3664 4412.2137) (2992.3664 3832.0611)
    ))
    ; P0926 -- see feature_dimensions_mm.csv
    ("03_FRAMES_DOORS" 0 (
      (3015.2672 4473.2824) (3022.9008 4473.2824) (3054.9008 4473.2824) (3177.1603 4473.2824) (3210.626 4473.2824)
      (3332.8855 4473.2824) (3366.3511 4473.2824) (3488.6107 4473.2824) (3522.0763 4473.2824) (3644.3359 4473.2824)
      (3677.8015 4473.2824) (3694.6565 4473.2824)
    ))
    ; P0927 -- see feature_dimensions_mm.csv
    ("03_FRAMES_DOORS" 0 (
      (3634.2443 4412.2137) (3532.1679 4412.2137) (3478.5191 4412.2137) (3376.4427 4412.2137) (3322.7939 4412.2137)
      (3220.7176 4412.2137) (3167.0687 4412.2137) (3064.9924 4412.2137) (3022.9008 4412.2137) (3015.2672 4412.2137)
    ))
    ; P0928 -- see feature_dimensions_mm.csv
    ("03_FRAMES_DOORS" 0 (
      (3015.2672 3832.0611) (3015.2672 4412.2137)
    ))
    ; P0929 -- see feature_dimensions_mm.csv
    ("03_FRAMES_DOORS" 0 (
      (3069.0687 5679.3893) (3074.8092 5679.3893)
    ))
    ; P0930 -- see feature_dimensions_mm.csv
    ("03_FRAMES_DOORS" 0 (
      (3801.5267 4473.2824) (3801.5267 5282.4427) (3798.5038 5312.7634) (3789.7099 5341.8779) (3775.5725 5369.8168)
      (3756.4885 5396.5649) (3732.8855 5422.1374) (3705.1756 5446.5496) (3673.771 5469.8015) (3639.084 5491.9084)
      (3601.542 5512.8702) (3561.542 5532.687) (3519.5267 5551.374) (3475.8779 5568.9313) (3431.0382 5585.374)
      (3385.4046 5600.7176) (3339.3893 5614.9466) (3293.4351 5628.0916) (3247.9389 5640.1374) (3203.2977 5651.1145)
      (3159.9542 5661.0076) (3118.3206 5669.8473) (3078.7939 5677.6183) (3069.0687 5679.3893)
    ))
    ; P0931 -- see feature_dimensions_mm.csv
    ("03_FRAMES_DOORS" 0 (
      (3801.5267 4473.2824) (3908.3969 4473.2824) (3908.3969 5374.0458) (3904.9771 5405.4809) (3895.0534 5435.6794)
      (3879.0687 5464.6565) (3857.5267 5492.3969) (3830.855 5518.916) (3799.5573 5544.229) (3764.0763 5568.3511)
      (3724.9008 5591.2672) (3682.4885 5613.0076) (3637.313 5633.5573) (3589.8321 5652.9313) (3540.5344 5671.145)
      (3489.8779 5688.1985) (3438.3359 5704.1069) (3386.3664 5718.8702) (3334.4427 5732.5038) (3283.0382 5744.9924)
      (3232.626 5756.3664) (3183.6641 5766.6412) (3136.626 5775.8015) (3096.7481 5782.9924)
    ))
    ; P0932 -- see feature_dimensions_mm.csv
    ("03_FRAMES_DOORS" 0 (
      (3129.771 1633.5878) (3129.771 1862.5954)
    ))
    ; P0933 -- see feature_dimensions_mm.csv
    ("03_FRAMES_DOORS" 0 (
      (3328.2443 9312.9771) (3328.2443 9145.0382) (3328.2443 8946.5649) (3177.0992 8946.5649)
    ))
    ; P0934 -- see feature_dimensions_mm.csv
    ("03_FRAMES_DOORS" 0 (
      (3221.374 931.2977) (3221.374 656.4885) (3221.374 442.7481)
    ))
    ; P0935 -- see feature_dimensions_mm.csv
    ("03_FRAMES_DOORS" 0 (
      (3292.4275 5501.6641) (3252.4275 5513.3435)
    ))
    ; P0936 -- see feature_dimensions_mm.csv
    ("03_FRAMES_DOORS" 0 (
      (3283.7557 2259.542) (3269.3893 2233.1145)
    ))
    ; P0937 -- see feature_dimensions_mm.csv
    ("03_FRAMES_DOORS" 0 (
      (3396.1832 5466.3969) (3372.1832 5475.3893) (3332.4733 5489.0229) (3296.9771 5500.229)
    ))
    ; P0938 -- see feature_dimensions_mm.csv
    ("03_FRAMES_DOORS" 0 (
      (3498.3664 5422.1679) (3485.7863 5428.5344) (3449.2061 5445.145) (3434.9313 5451.0229) (3419.145 5457.5115)
      (3412.3053 5460.3206) (3411.2214 5460.7634)
    ))
    ; P0939 -- see feature_dimensions_mm.csv
    ("03_FRAMES_DOORS" 0 (
      (3481.0687 2441.313) (3454.1985 2427.1908)
    ))
    ; P0940 -- see feature_dimensions_mm.csv
    ("03_FRAMES_DOORS" 0 (
      (3694.6565 5180.9924) (3694.6565 5206.1069) (3692.0305 5233.0534) (3684.3817 5258.9466) (3672.0611 5283.771)
      (3667.3588 5290.5038) (3655.4504 5307.542) (3634.916 5330.2901) (3625.1603 5339.0534) (3610.7939 5351.9847)
      (3583.4656 5372.6565) (3553.2672 5392.3053) (3523.5267 5409.2519)
    ))
    ; P0941 -- see feature_dimensions_mm.csv
    ("03_FRAMES_DOORS" 0 (
      (3574.3053 2474.7328) (3566.5038 2472.9466)
    ))
    ; P0942 -- see feature_dimensions_mm.csv
    ("03_FRAMES_DOORS" 0 (
      (3594.1985 2381.6794) (3593.5573 2384.7023) (3586.2595 2382.9008) (3561.8779 2375.0687) (3538.0458 2365.5725)
      (3514.8397 2354.4427) (3492.3664 2341.7252) (3470.7328 2327.4809) (3450.0305 2311.771) (3430.3359 2294.6565)
      (3411.7405 2276.2137) (3394.3206 2256.5191) (3378.1527 2235.6794) (3363.3282 2213.7405) (3349.8626 2190.8397)
      (3337.8626 2167.0534) (3327.3435 2142.4733) (3318.3664 2117.2366) (3310.9771 2091.4198) (3305.1908 2065.145)
      (3301.0382 2038.5344) (3298.5496 2011.6947) (3297.7099 1984.7328) (3297.7099 503.8168) (4076.3359 503.8168)
      (4076.3359 1984.7328) (4075.4962 2011.6947) (4073.0076 2038.5344) (4068.855 2065.145) (4063.0687 2091.4198)
      (4055.6794 2117.2366) (4046.7023 2142.4733) (4036.1832 2167.0534) (4024.1832 2190.8397) (4010.7176 2213.7405)
      (3995.8931 2235.6794) (3979.7252 2256.5191) (3962.3053 2276.2137) (3943.7099 2294.6565) (3924.0153 2311.771)
      (3903.313 2327.4809) (3881.6794 2341.7252) (3859.2061 2354.4427) (3836.0 2365.5725) (3812.1679 2375.0687)
      (3787.7863 2382.9008) (3780.4885 2384.7023) (3779.8473 2381.6794)
    ))
    ; P0943 -- see feature_dimensions_mm.csv
    ("03_FRAMES_DOORS" 0 (
      (3741.9847 8946.5649) (3618.3206 8946.5649) (3618.3206 9145.0382) (3618.3206 9251.9084)
    ))
    ; P0944 -- see feature_dimensions_mm.csv
    ("03_FRAMES_DOORS" 0 (
      (3661.5115 3832.0611) (3694.6565 3832.0611)
    ))
    ; P0945 -- see feature_dimensions_mm.csv
    ("03_FRAMES_DOORS" 0 (
      (3694.6565 4412.2137) (3687.8931 4412.2137)
    ))
    ; P0946 -- see feature_dimensions_mm.csv
    ("03_FRAMES_DOORS" 0 (
      (3694.6565 5055.6336) (3694.6565 5170.6718)
    ))
    ; P0947 -- see feature_dimensions_mm.csv
    ("03_FRAMES_DOORS" 0 (
      (3694.6565 5027.9237) (3694.6565 5044.8855)
    ))
    ; P0948 -- see feature_dimensions_mm.csv
    ("03_FRAMES_DOORS" 0 (
      (3694.6565 4995.3282) (3694.6565 5012.2901)
    ))
    ; P0949 -- see feature_dimensions_mm.csv
    ("03_FRAMES_DOORS" 0 (
      (3694.6565 4869.542) (3694.6565 4984.5649)
    ))
    ; P0950 -- see feature_dimensions_mm.csv
    ("03_FRAMES_DOORS" 0 (
      (3694.6565 4744.1832) (3694.6565 4859.2214)
    ))
    ; P0951 -- see feature_dimensions_mm.csv
    ("03_FRAMES_DOORS" 0 (
      (3694.6565 4716.4733) (3694.6565 4733.4351)
    ))
    ; P0952 -- see feature_dimensions_mm.csv
    ("03_FRAMES_DOORS" 0 (
      (3694.6565 4683.8779) (3694.6565 4700.8397)
    ))
    ; P0953 -- see feature_dimensions_mm.csv
    ("03_FRAMES_DOORS" 0 (
      (3694.6565 4558.0916) (3694.6565 4673.1145)
    ))
    ; P0954 -- see feature_dimensions_mm.csv
    ("03_FRAMES_DOORS" 0 (
      (3694.6565 4473.2824) (3694.6565 4547.771)
    ))
    ; P0955 -- see feature_dimensions_mm.csv
    ("03_FRAMES_DOORS" 0 (
      (3694.6565 4473.2824) (3801.5267 4473.2824)
    ))
    ; P0956 -- see feature_dimensions_mm.csv
    ("03_FRAMES_DOORS" 0 (
      (3755.7252 3832.0611) (3801.5267 3832.0611) (3801.5267 4412.2137) (3755.7252 4412.2137) (3725.1908 4412.2137)
      (3694.6565 4412.2137)
    ))
    ; P0957 -- see feature_dimensions_mm.csv
    ("03_FRAMES_DOORS" 0 (
      (3694.6565 4405.0229) (3694.6565 4412.2137)
    ))
    ; P0958 -- see feature_dimensions_mm.csv
    ("03_FRAMES_DOORS" 0 (
      (3694.6565 4372.4275) (3694.6565 4389.3893)
    ))
    ; P0959 -- see feature_dimensions_mm.csv
    ("03_FRAMES_DOORS" 0 (
      (3694.6565 4246.6412) (3694.6565 4361.6641)
    ))
    ; P0960 -- see feature_dimensions_mm.csv
    ("03_FRAMES_DOORS" 0 (
      (3694.6565 4121.2824) (3694.6565 4236.3206)
    ))
    ; P0961 -- see feature_dimensions_mm.csv
    ("03_FRAMES_DOORS" 0 (
      (3694.6565 4093.5725) (3694.6565 4110.5344)
    ))
    ; P0962 -- see feature_dimensions_mm.csv
    ("03_FRAMES_DOORS" 0 (
      (3694.6565 4060.9771) (3694.6565 4077.9389)
    ))
    ; P0963 -- see feature_dimensions_mm.csv
    ("03_FRAMES_DOORS" 0 (
      (3694.6565 3935.1908) (3694.6565 4050.2137)
    ))
    ; P0964 -- see feature_dimensions_mm.csv
    ("03_FRAMES_DOORS" 0 (
      (3694.6565 3832.0611) (3694.6565 3924.8702)
    ))
    ; P0965 -- see feature_dimensions_mm.csv
    ("03_FRAMES_DOORS" 0 (
      (3694.6565 3832.0611) (3725.1908 3832.0611)
    ))
    ; P0966 -- see feature_dimensions_mm.csv
    ("03_FRAMES_DOORS" 0 (
      (3816.7939 9145.0382) (3816.7939 9038.1679) (3816.7939 8946.5649)
    ))
    ; P0967 -- see feature_dimensions_mm.csv
    ("03_FRAMES_DOORS" 0 (
      (3908.3969 3832.0611) (3908.3969 4412.2137)
    ))
    ; P0968 -- see feature_dimensions_mm.csv
    ("03_FRAMES_DOORS" 0 (
      (4117.2214 2205.8015) (4104.6565 2233.1145)
    ))
    ; P0969 -- see feature_dimensions_mm.csv
    ("03_FRAMES_DOORS" 0 (
      (4152.6718 442.7481) (4152.6718 656.4885) (4152.6718 931.2977)
    ))
    ; P0970 -- see feature_dimensions_mm.csv
    ("03_FRAMES_DOORS" 0 (
      (4244.2748 656.4885) (4519.084 656.4885)
    ))
    ; P0971 -- see feature_dimensions_mm.csv
    ("03_FRAMES_DOORS" 0 (
      (5297.7099 961.8321) (5246.8244 1053.4351) (5221.374 1099.2366) (6122.1374 1099.2366) (6096.687 1053.4351)
      (6045.8015 961.8321)
    ))
    ; P0972 -- see feature_dimensions_mm.csv
    ("03_FRAMES_DOORS" 0 (
      (6335.8779 961.8321) (6284.9924 1053.4351) (6259.542 1099.2366) (7480.916 1099.2366) (7455.4656 1053.4351)
      (7404.5802 961.8321)
    ))
    ; P0973 -- see feature_dimensions_mm.csv
    ("03_FRAMES_DOORS" 0 (
      (7618.3206 1099.2366) (7618.3206 1587.7863) (7618.3206 2213.7405) (7618.3206 2839.6947) (7618.3206 3465.6489)
    ))
    ; P0974 -- see feature_dimensions_mm.csv
    ("03_FRAMES_DOORS" 0 (
      (8473.2824 1099.2366) (7618.3206 1099.2366)
    ))
    ; P0975 -- see feature_dimensions_mm.csv
    ("03_FRAMES_DOORS" 0 (
      (7618.3206 1099.2366) (7643.771 1053.4351)
    ))
    ; P0976 -- see feature_dimensions_mm.csv
    ("03_FRAMES_DOORS" 0 (
      (7643.771 1053.4351) (7618.3206 1053.4351) (7618.3206 1099.2366)
    ))
    ; P0977 -- see feature_dimensions_mm.csv
    ("03_FRAMES_DOORS" 0 (
      (8473.2824 1053.4351) (7643.771 1053.4351)
    ))
    ; P0978 -- see feature_dimensions_mm.csv
    ("03_FRAMES_DOORS" 0 (
      (7643.771 1053.4351) (7694.6565 961.8321) (8442.7481 961.8321) (8473.2824 1016.7939) (8473.2824 1053.4351)
    ))
    ; P0979 -- see feature_dimensions_mm.csv
    ("03_FRAMES_DOORS" 0 (
      (7664.7634 5554.5954) (7678.6565 5580.1527)
    ))
    ; P0980 -- see feature_dimensions_mm.csv
    ("03_FRAMES_DOORS" 0 (
      (7711.3893 5628.3053) (7730.0916 5650.7023)
    ))
    ; P0981 -- see feature_dimensions_mm.csv
    ("03_FRAMES_DOORS" 0 (
      (7750.229 5671.8473) (7771.7405 5691.6489)
    ))
    ; P0982 -- see feature_dimensions_mm.csv
    ("03_FRAMES_DOORS" 0 (
      (7952.1374 5786.4427) (7980.8397 5793.0229)
    ))
    ; P0983 -- see feature_dimensions_mm.csv
    ("03_FRAMES_DOORS" 0 (
      (8098.1527 5800.5802) (8127.4962 5797.7405)
    ))
    ; P0984 -- see feature_dimensions_mm.csv
    ("03_FRAMES_DOORS" 0 (
      (8426.0153 5628.3053) (8443.1756 5604.7634)
    ))
    ; P0985 -- see feature_dimensions_mm.csv
    ("03_FRAMES_DOORS" 0 (
      (8473.2824 1099.2366) (8473.2824 3618.3206)
    ))
    ; P0986 -- see feature_dimensions_mm.csv
    ("03_FRAMES_DOORS" 0 (
      (8473.2824 1053.4351) (8473.2824 1099.2366)
    ))
    ; P0987 -- see feature_dimensions_mm.csv
    ("03_FRAMES_DOORS" 0 (
      (8518.1221 5387.7405) (8519.084 5358.7786)
    ))
    ; P0988 -- see feature_dimensions_mm.csv
    ("03_FRAMES_DOORS" 0 (
      (8748.0916 320.6107) (10229.0076 320.6107) (10244.2748 320.6107)
    ))
    ; P0989 -- see feature_dimensions_mm.csv
    ("03_FRAMES_DOORS" 0 (
      (10244.2748 320.6107) (10335.8779 320.6107) (10335.8779 3404.5802) (8656.4885 3404.5802) (8656.4885 320.6107)
      (8702.2901 320.6107) (8748.0916 320.6107)
    ))
    ; P0990 -- see feature_dimensions_mm.csv
    ("03_FRAMES_DOORS" 0 (
      (10244.2748 320.6107) (10244.2748 3312.9771) (8748.0916 3312.9771) (8748.0916 396.9466) (8748.0916 320.6107)
    ))
    ; P0991 -- see feature_dimensions_mm.csv
    ("03_FRAMES_DOORS" 0 (
      (8885.4962 4473.2824) (8793.8931 4473.2824) (8793.8931 5358.7786) (8796.4427 5382.3511) (8803.8473 5405.0076)
    ))
    ; P0992 -- see feature_dimensions_mm.csv
    ("03_FRAMES_DOORS" 0 (
      (8815.771 5426.7328) (8831.8473 5447.542) (8851.7252 5467.4351)
    ))
    ; P0993 -- see feature_dimensions_mm.csv
    ("03_FRAMES_DOORS" 0 (
      (8885.4962 4473.2824) (8946.5649 4473.2824)
    ))
    ; P0994 -- see feature_dimensions_mm.csv
    ("03_FRAMES_DOORS" 0 (
      (10091.6031 4473.2824) (10091.6031 5267.1756) (10089.3893 5289.6336) (10082.9618 5311.2061) (10072.6107 5331.8931)
      (10058.6565 5351.7099) (10041.3893 5370.6565) (10021.1145 5388.7328) (9998.1527 5405.9695) (9972.7786 5422.3359)
      (9945.313 5437.8626) (9916.0611 5452.5344) (9885.3282 5466.3817) (9853.4046 5479.3893) (9820.5954 5491.5725)
      (9787.2214 5502.9313) (9753.5573 5513.4809) (9719.9389 5523.2061) (9686.6565 5532.1374) (9654.0153 5540.2595)
      (9622.3053 5547.6031) (9591.8473 5554.1374) (9562.9466 5559.8931) (9535.8931 5564.8855) (9510.9924 5569.084)
      (9488.5496 5572.5191) (9466.1069 5569.084) (9441.2061 5564.8855) (9414.1527 5559.8931) (9385.2519 5554.1374)
      (9354.7939 5547.6031) (9323.084 5540.2595) (9290.4427 5532.1374) (9257.1603 5523.2061) (9223.542 5513.4809)
      (9189.8779 5502.9313) (9156.5038 5491.5725) (9123.7099 5479.3893) (9091.771 5466.3817) (9061.0382 5452.5344)
      (9031.7863 5437.8626) (9004.3206 5422.3359) (8978.9466 5405.9695) (8955.9847 5388.7328) (8935.7099 5370.6565)
      (8918.4427 5351.7099) (8904.4885 5331.8931) (8894.1374 5311.2061) (8887.7099 5289.6336) (8885.4962 5267.1756)
      (8885.4962 4473.2824)
    ))
    ; P0995 -- see feature_dimensions_mm.csv
    ("03_FRAMES_DOORS" 0 (
      (8946.5649 4412.2137) (8885.4962 4412.2137)
    ))
    ; P0996 -- see feature_dimensions_mm.csv
    ("03_FRAMES_DOORS" 0 (
      (8885.4962 4412.2137) (8885.4962 3832.0611)
    ))
    ; P0997 -- see feature_dimensions_mm.csv
    ("03_FRAMES_DOORS" 0 (
      (8885.4962 4412.2137) (8793.8931 4412.2137) (8793.8931 3832.0611) (8885.4962 3832.0611)
    ))
    ; P0998 -- see feature_dimensions_mm.csv
    ("03_FRAMES_DOORS" 0 (
      (8885.4962 3832.0611) (8946.5649 3832.0611)
    ))
    ; P0999 -- see feature_dimensions_mm.csv
    ("03_FRAMES_DOORS" 0 (
      (8946.5649 4473.2824) (9087.5725 4473.2824) (9095.6336 4473.2824) (9232.6107 4473.2824) (9240.6718 4473.2824)
      (9377.6489 4473.2824) (9385.7099 4473.2824) (9465.6489 4473.2824)
    ))
    ; P1000 -- see feature_dimensions_mm.csv
    ("03_FRAMES_DOORS" 0 (
      (9130.4427 5404.5496) (9104.3359 5391.4656) (9078.0458 5376.7939) (9053.3588 5361.2672) (9030.5496 5344.9008)
      (9009.9084 5327.6641) (8991.6947 5309.5878) (8976.1679 5290.6412) (8963.6336 5270.8244) (8954.3359 5250.1374)
      (8948.5496 5228.5649) (8946.5649 5206.1069) (8946.5649 4473.2824)
    ))
    ; P1001 -- see feature_dimensions_mm.csv
    ("03_FRAMES_DOORS" 0 (
      (9338.9313 4412.2137) (9279.3893 4412.2137) (9247.5878 4412.2137) (9225.6947 4412.2137) (9193.8931 4412.2137)
      (9134.3511 4412.2137) (9102.5496 4412.2137) (9080.6565 4412.2137) (9048.855 4412.2137) (8946.5649 4412.2137)
    ))
    ; P1002 -- see feature_dimensions_mm.csv
    ("03_FRAMES_DOORS" 0 (
      (8946.5649 4412.2137) (8946.5649 3832.0611)
    ))
    ; P1003 -- see feature_dimensions_mm.csv
    ("03_FRAMES_DOORS" 0 (
      (8946.5649 3832.0611) (9048.855 3832.0611) (9080.6565 3832.0611) (9102.5496 3832.0611) (9134.3511 3832.0611)
      (9193.8931 3832.0611) (9225.6947 3832.0611) (9247.5878 3832.0611) (9279.3893 3832.0611) (9338.9313 3832.0611)
      (9370.7328 3832.0611)
    ))
    ; P1004 -- see feature_dimensions_mm.csv
    ("03_FRAMES_DOORS" 0 (
      (9280.5954 5462.1374) (9275.2672 5460.4275) (9250.3664 5452.4122) (9220.1221 5441.8626) (9206.7634 5436.8092)
      (9190.1374 5430.5038) (9160.6565 5418.3206) (9131.9542 5405.313)
    ))
    ; P1005 -- see feature_dimensions_mm.csv
    ("03_FRAMES_DOORS" 0 (
      (9183.2824 5617.3893) (9222.0 5627.6183) (9260.3511 5636.9924) (9297.9542 5645.5267) (9334.4733 5653.2214)
      (9369.5573 5660.0916)
    ))
    ; P1006 -- see feature_dimensions_mm.csv
    ("03_FRAMES_DOORS" 0 (
      (9222.3817 2758.4733) (9207.6947 2751.6336) (9171.0534 2733.1908) (9134.7176 2713.2977) (9099.0076 2691.9847)
      (9064.2595 2669.2214) (9030.7939 2644.9924) (8998.9466 2619.2977) (8969.0534 2592.1374) (8941.4351 2563.4962)
      (8916.4275 2533.3435) (8894.3511 2501.7099) (8875.5573 2468.5496) (8860.3664 2433.8626) (8849.0992 2397.6641)
      (8842.1069 2359.9084) (8839.6947 2320.6107) (8839.6947 396.9466) (8839.6947 335.8779) (10152.6718 335.8779)
      (10152.6718 396.9466) (10152.6718 2320.6107) (10150.2595 2359.9084) (10143.2672 2397.6641) (10132.0 2433.8626)
      (10116.8092 2468.5496) (10098.0153 2501.7099) (10075.9389 2533.3435) (10050.9313 2563.4962) (10023.313 2592.1374)
      (9993.4198 2619.2977) (9961.5725 2644.9924) (9928.1069 2669.2214) (9893.3588 2691.9847) (9857.6489 2713.2977)
      (9821.313 2733.1908) (9784.6718 2751.6336) (9769.0229 2758.9313)
    ))
    ; P1007 -- see feature_dimensions_mm.csv
    ("03_FRAMES_DOORS" 0 (
      (9316.0611 2798.5191) (9301.771 2792.7939) (9280.5191 2784.3053) (9276.2901 2782.4733) (9244.2901 2768.6718)
    ))
    ; P1008 -- see feature_dimensions_mm.csv
    ("03_FRAMES_DOORS" 0 (
      (9711.2824 5457.3893) (9696.5038 5462.1374) (9666.5954 5471.0687) (9637.2519 5479.1908) (9608.7634 5486.5344)
      (9581.3893 5493.0687) (9555.4046 5498.8244) (9531.0992 5503.8168) (9508.7176 5508.0153) (9488.5496 5511.4504)
      (9468.3817 5508.0153) (9446.0 5503.8168) (9421.6947 5498.8244) (9395.7099 5493.0687) (9368.3359 5486.5344)
      (9339.8473 5479.1908) (9314.8855 5472.2901) (9310.5038 5471.0687) (9302.4885 5468.6718) (9286.1374 5463.8015)
    ))
    ; P1009 -- see feature_dimensions_mm.csv
    ("03_FRAMES_DOORS" 0 (
      (9465.6489 4412.2137) (9450.3817 4412.2137) (9424.4275 4412.2137) (9392.626 4412.2137) (9370.7328 4412.2137)
    ))
    ; P1010 -- see feature_dimensions_mm.csv
    ("03_FRAMES_DOORS" 0 (
      (9641.8015 2811.3588) (9619.4962 2819.0534) (9608.6412 2822.8092) (9577.1603 2832.8855) (9547.7099 2841.5878)
      (9520.6107 2848.9466) (9496.1832 2854.9618) (9471.7557 2848.9466) (9444.6565 2841.5878) (9415.2061 2832.8855)
      (9383.7252 2822.8092) (9372.4733 2818.916)
    ))
    ; P1011 -- see feature_dimensions_mm.csv
    ("03_FRAMES_DOORS" 0 (
      (9383.9389 2509.2519) (9383.0076 2509.1145) (9346.0305 2501.3893) (9309.6947 2491.542) (9274.1679 2479.5725)
      (9239.5878 2465.5573) (9206.1069 2449.542) (9173.8626 2431.6031) (9143.0076 2411.8168) (9113.6641 2390.2748)
      (9085.9542 2367.0534) (9060.0 2342.2595) (9035.9237 2316.0) (9013.8015 2288.3817) (8993.7557 2259.542)
      (8975.8626 2229.5878) (8960.1985 2198.6412) (8946.8244 2166.855) (8935.8015 2134.3511) (8927.1756 2101.2672)
      (8920.9924 2067.7557) (8917.2672 2033.9542) (8916.0305 2000.0) (8916.0305 396.9466) (8916.0305 381.6794)
      (10076.3359 381.6794) (10076.3359 396.9466) (10076.3359 2000.0) (10075.0992 2033.9542) (10071.374 2067.7557)
      (10065.1908 2101.2672) (10056.5649 2134.3511) (10045.542 2166.855) (10032.1679 2198.6412) (10016.5038 2229.5878)
      (9998.6107 2259.542) (9978.5649 2288.3817) (9956.4427 2316.0) (9932.3664 2342.2595) (9906.4122 2367.0534)
      (9878.7023 2390.2748) (9849.3588 2411.8168) (9818.5038 2431.6031) (9786.2595 2449.542) (9752.7786 2465.5573)
      (9718.1985 2479.5725) (9682.6718 2491.542) (9646.3359 2501.3893) (9609.3588 2509.1145) (9608.4427 2509.2519)
      (9584.1221 2381.6794)
    ))
    ; P1012 -- see feature_dimensions_mm.csv
    ("03_FRAMES_DOORS" 0 (
      (9424.4275 3832.0611) (9450.3817 3832.0611) (9465.6489 3832.0611)
    ))
    ; P1013 -- see feature_dimensions_mm.csv
    ("03_FRAMES_DOORS" 0 (
      (9434.0153 5671.374) (9462.7023 5675.7863) (9488.5496 5679.3893)
    ))
    ; P1014 -- see feature_dimensions_mm.csv
    ("03_FRAMES_DOORS" 0 (
      (9465.6489 4473.2824) (9511.4504 4473.2824)
    ))
    ; P1015 -- see feature_dimensions_mm.csv
    ("03_FRAMES_DOORS" 0 (
      (9511.4504 4473.2824) (9511.4504 5496.1832) (9465.6489 5496.1832) (9465.6489 4473.2824)
    ))
    ; P1016 -- see feature_dimensions_mm.csv
    ("03_FRAMES_DOORS" 0 (
      (9465.6489 3832.0611) (9473.2824 3832.0611) (9473.2824 4412.2137) (9465.6489 4412.2137)
    ))
    ; P1017 -- see feature_dimensions_mm.csv
    ("03_FRAMES_DOORS" 0 (
      (9465.6489 4412.2137) (9465.6489 3832.0611)
    ))
    ; P1018 -- see feature_dimensions_mm.csv
    ("03_FRAMES_DOORS" 0 (
      (9503.8168 4412.2137) (9503.8168 3832.0611) (9511.4504 3832.0611)
    ))
    ; P1019 -- see feature_dimensions_mm.csv
    ("03_FRAMES_DOORS" 0 (
      (9511.4504 4473.2824) (9526.7176 4473.2824) (9530.7481 4473.2824) (9667.7252 4473.2824) (9675.7863 4473.2824)
      (9812.7634 4473.2824) (9820.8244 4473.2824) (9957.8015 4473.2824) (9965.8626 4473.2824) (10030.5344 4473.2824)
    ))
    ; P1020 -- see feature_dimensions_mm.csv
    ("03_FRAMES_DOORS" 0 (
      (9511.4504 3832.0611) (9511.4504 4412.2137)
    ))
    ; P1021 -- see feature_dimensions_mm.csv
    ("03_FRAMES_DOORS" 0 (
      (9511.4504 3832.0611) (9526.7176 3832.0611)
    ))
    ; P1022 -- see feature_dimensions_mm.csv
    ("03_FRAMES_DOORS" 0 (
      (9569.4656 3832.0611) (9629.0076 3832.0611)
    ))
    ; P1023 -- see feature_dimensions_mm.csv
    ("03_FRAMES_DOORS" 0 (
      (9715.2824 2782.8244) (9711.8473 2784.3053) (9689.9695 2793.0534)
    ))
    ; P1024 -- see feature_dimensions_mm.csv
    ("03_FRAMES_DOORS" 0 (
      (9786.9618 5430.5038) (9756.9771 5441.8626) (9726.7328 5452.4122)
    ))
    ; P1025 -- see feature_dimensions_mm.csv
    ("03_FRAMES_DOORS" 0 (
      (9960.1832 5333.5115) (9946.5496 5344.9008) (9923.7405 5361.2672) (9899.0534 5376.7939) (9872.7634 5391.4656)
      (9845.145 5405.313) (9816.458 5418.3206) (9790.0458 5429.2366)
    ))
    ; P1026 -- see feature_dimensions_mm.csv
    ("03_FRAMES_DOORS" 0 (
      (9859.542 3832.0611) (9919.084 3832.0611) (9950.8855 3832.0611)
    ))
    ; P1027 -- see feature_dimensions_mm.csv
    ("03_FRAMES_DOORS" 0 (
      (9985.4046 5309.5878) (9979.6336 5315.3282) (9967.542 5327.3282)
    ))
    ; P1028 -- see feature_dimensions_mm.csv
    ("03_FRAMES_DOORS" 0 (
      (9972.7786 3832.0611) (10004.5802 3832.0611) (10030.5344 3832.0611)
    ))
    ; P1029 -- see feature_dimensions_mm.csv
    ("03_FRAMES_DOORS" 0 (
      (10028.5344 5228.626) (10022.7634 5250.1374) (10013.4656 5270.8244) (10005.7252 5283.0687) (10000.9313 5290.6412)
      (9998.3664 5293.7557) (9989.6947 5304.3664)
    ))
    ; P1030 -- see feature_dimensions_mm.csv
    ("03_FRAMES_DOORS" 0 (
      (10030.5344 4473.2824) (10030.5344 4517.6641) (10030.5344 4550.7328) (10030.5344 4573.0382) (10030.5344 4606.1069)
      (10030.5344 4618.0916) (10030.5344 4650.7176) (10030.5344 4807.7405) (10030.5344 4840.8092) (10030.5344 4863.1145)
      (10030.5344 4896.1832) (10030.5344 4908.1679) (10030.5344 4940.7939) (10030.5344 5097.8168) (10030.5344 5130.8855)
      (10030.5344 5153.1908) (10030.5344 5186.2595) (10030.5344 5198.2443) (10030.5344 5206.1069) (10028.5496 5228.5649)
    ))
    ; P1031 -- see feature_dimensions_mm.csv
    ("03_FRAMES_DOORS" 0 (
      (10030.5344 4473.2824) (10091.6031 4473.2824)
    ))
    ; P1032 -- see feature_dimensions_mm.csv
    ("03_FRAMES_DOORS" 0 (
      (10030.5344 4360.6412) (10030.5344 4412.2137)
    ))
    ; P1033 -- see feature_dimensions_mm.csv
    ("03_FRAMES_DOORS" 0 (
      (10030.5344 4316.0305) (10030.5344 4328.0153)
    ))
    ; P1034 -- see feature_dimensions_mm.csv
    ("03_FRAMES_DOORS" 0 (
      (10030.5344 4070.5649) (10030.5344 4227.5878)
    ))
    ; P1035 -- see feature_dimensions_mm.csv
    ("03_FRAMES_DOORS" 0 (
      (10030.5344 4025.9542) (10030.5344 4037.9389)
    ))
    ; P1036 -- see feature_dimensions_mm.csv
    ("03_FRAMES_DOORS" 0 (
      (10030.5344 3832.0611) (10030.5344 3937.5115)
    ))
    ; P1037 -- see feature_dimensions_mm.csv
    ("03_FRAMES_DOORS" 0 (
      (10030.5344 3832.0611) (10091.6031 3832.0611)
    ))
    ; P1038 -- see feature_dimensions_mm.csv
    ("03_FRAMES_DOORS" 0 (
      (10125.374 5467.4351) (10145.2519 5447.542) (10161.3282 5426.7328) (10173.2519 5405.0076) (10180.6565 5382.3511)
      (10183.2061 5358.7786) (10183.2061 4473.2824) (10091.6031 4473.2824)
    ))
    ; P1039 -- see feature_dimensions_mm.csv
    ("03_FRAMES_DOORS" 0 (
      (10091.6031 3832.0611) (10091.6031 4412.2137)
    ))
    ; P1040 -- see feature_dimensions_mm.csv
    ("03_FRAMES_DOORS" 0 (
      (10091.6031 3832.0611) (10183.2061 3832.0611)
    ))
    ; P1041 -- see feature_dimensions_mm.csv
    ("03_FRAMES_DOORS" 0 (
      (10580.1527 656.4885) (10854.9618 656.4885)
    ))
    ; P1042 -- see feature_dimensions_mm.csv
    ("03_FRAMES_DOORS" 0 (
      (10850.3206 2061.0687) (10783.6489 2061.0687)
    ))
    ; P1043 -- see feature_dimensions_mm.csv
    ("03_FRAMES_DOORS" 0 (
      (10809.1603 1865.0382) (10809.1603 1862.5954) (10854.9618 1862.5954) (10854.9618 656.4885)
    ))
    ; P1044 -- see feature_dimensions_mm.csv
    ("03_FRAMES_DOORS" 0 (
      (10809.1603 1865.0382) (10809.1603 1969.4656) (10825.4809 1989.0534)
    ))
    ; P1045 -- see feature_dimensions_mm.csv
    ("03_FRAMES_DOORS" 0 (
      (10825.4809 1989.0534) (10819.7252 1965.8321) (10813.8626 1932.4733) (10810.3359 1898.8244) (10809.1603 1865.0382)
    ))
    ; P1046 -- see feature_dimensions_mm.csv
    ("03_FRAMES_DOORS" 0 (
      (10829.9084 2155.7252) (10811.0687 2122.5954)
    ))
    ; P1047 -- see feature_dimensions_mm.csv
    ("03_FRAMES_DOORS" 0 (
      (10825.4809 1989.0534) (10885.4962 2061.0687) (10850.3206 2061.0687)
    ))
    ; P1048 -- see feature_dimensions_mm.csv
    ("03_FRAMES_DOORS" 0 (
      (11265.9542 2351.145) (11261.4962 2373.2977) (11251.5573 2371.7557) (11216.5344 2364.0763) (11182.1069 2354.2595)
      (11148.4427 2342.3511) (11115.6947 2328.3969) (11083.9695 2312.458) (11053.4198 2294.6107) (11024.1985 2274.916)
      (10996.3969 2253.4656) (10970.1374 2230.3511) (10945.5573 2205.6794) (10922.7328 2179.542) (10901.7863 2152.0611)
      (10882.7939 2123.3588) (10865.8473 2093.542) (10850.9924 2062.7481) (10850.3206 2061.0687)
    ))
    ; P1049 -- see feature_dimensions_mm.csv
    ("03_FRAMES_DOORS" 0 (
      (10854.9618 656.4885) (10870.229 656.4885)
    ))
    ; P1050 -- see feature_dimensions_mm.csv
    ("03_FRAMES_DOORS" 0 (
      (10870.229 656.4885) (11847.3282 656.4885)
    ))
    ; P1051 -- see feature_dimensions_mm.csv
    ("03_FRAMES_DOORS" 0 (
      (11847.3282 656.4885) (11847.3282 1861.374) (11846.2748 1891.4046) (11843.145 1921.313) (11837.9389 1950.9618)
      (11830.687 1980.229) (11821.4046 2008.9924) (11810.1374 2037.1145) (11796.9466 2064.4885) (11781.8779 2090.9924)
      (11764.9924 2116.5191) (11746.3664 2140.9466) (11726.0916 2164.1679) (11704.229 2186.1069) (11680.9008 2206.6412)
      (11656.1832 2225.7099) (11630.1985 2243.2214) (11603.0534 2259.084) (11574.855 2273.2519) (11545.7405 2285.6489)
      (11515.8168 2296.2443) (11485.2214 2304.9618) (11454.0916 2311.7863) (11422.5496 2316.687) (11390.7328 2319.6336)
      (11358.7786 2320.6107) (11326.8244 2319.6336) (11295.0076 2316.687) (11263.4656 2311.7863) (11232.3359 2304.9618)
      (11201.7405 2296.2443) (11171.8168 2285.6489) (11142.7023 2273.2519) (11114.5038 2259.084) (11087.3588 2243.2214)
      (11061.374 2225.7099) (11036.6565 2206.6412) (11013.3282 2186.1069) (10991.4656 2164.1679) (10971.1908 2140.9466)
      (10952.5649 2116.5191) (10935.6794 2090.9924) (10920.6107 2064.4885) (10907.4198 2037.1145) (10896.1527 2008.9924)
      (10886.8702 1980.229) (10879.6183 1950.9618) (10874.4122 1921.313) (10871.2824 1891.4046) (10870.229 1861.374)
      (10870.229 656.4885)
    ))
    ; P1052 -- see feature_dimensions_mm.csv
    ("03_FRAMES_DOORS" 0 (
      (11019.4962 2346.0) (10987.0229 2324.1221)
    ))
    ; P1053 -- see feature_dimensions_mm.csv
    ("03_FRAMES_DOORS" 0 (
      (11088.6718 2383.542) (11053.4351 2365.8473)
    ))
    ; P1054 -- see feature_dimensions_mm.csv
    ("03_FRAMES_DOORS" 0 (
      (11236.6412 4473.2824) (11343.5115 4473.2824)
    ))
    ; P1055 -- see feature_dimensions_mm.csv
    ("03_FRAMES_DOORS" 0 (
      (11941.4198 5782.9924) (11901.542 5775.8015) (11854.5038 5766.6412) (11805.542 5756.3664) (11755.1298 5744.9924)
      (11703.7252 5732.5038) (11651.8015 5718.8702) (11599.8321 5704.1069) (11548.2901 5688.1985) (11497.6336 5671.145)
      (11448.3359 5652.9313) (11400.855 5633.5573) (11355.6794 5613.0076) (11313.2672 5591.2672) (11274.0916 5568.3511)
      (11238.6107 5544.229) (11207.313 5518.916) (11180.6412 5492.3969) (11159.0992 5464.6565) (11143.1145 5435.6794)
      (11133.1908 5405.4809) (11129.771 5374.0458) (11129.771 4473.2824) (11236.6412 4473.2824)
    ))
    ; P1056 -- see feature_dimensions_mm.csv
    ("03_FRAMES_DOORS" 0 (
      (11969.0992 5679.3893) (11959.374 5677.6183) (11919.8473 5669.8473) (11878.2137 5661.0076) (11834.8702 5651.1145)
      (11790.229 5640.1374) (11744.7328 5628.0916) (11698.7786 5614.9466) (11652.7634 5600.7176) (11607.1298 5585.374)
      (11562.2901 5568.9313) (11518.6412 5551.374) (11476.626 5532.687) (11436.626 5512.8702) (11399.084 5491.9084)
      (11364.3969 5469.8015) (11332.9924 5446.5496) (11305.2824 5422.1374) (11281.6794 5396.5649) (11262.5954 5369.8168)
      (11248.458 5341.8779) (11239.6641 5312.7634) (11236.6412 5282.4427) (11236.6412 4473.2824)
    ))
    ; P1057 -- see feature_dimensions_mm.csv
    ("03_FRAMES_DOORS" 0 (
      (12022.9008 4412.2137) (11993.2366 4412.2137) (11939.5878 4412.2137) (11837.5115 4412.2137) (11783.8626 4412.2137)
      (11681.7863 4412.2137) (11628.1374 4412.2137) (11526.0611 4412.2137) (11472.4122 4412.2137) (11343.5115 4412.2137)
      (11312.9771 4412.2137) (11236.6412 4412.2137)
    ))
    ; P1058 -- see feature_dimensions_mm.csv
    ("03_FRAMES_DOORS" 0 (
      (11236.6412 4412.2137) (11236.6412 3832.0611)
    ))
    ; P1059 -- see feature_dimensions_mm.csv
    ("03_FRAMES_DOORS" 0 (
      (11236.6412 4412.2137) (11129.771 4412.2137) (11129.771 3832.0611) (11236.6412 3832.0611)
    ))
    ; P1060 -- see feature_dimensions_mm.csv
    ("03_FRAMES_DOORS" 0 (
      (11236.6412 3832.0611) (11312.9771 3832.0611)
    ))
    ; P1061 -- see feature_dimensions_mm.csv
    ("03_FRAMES_DOORS" 0 (
      (11343.5115 4473.2824) (11482.5038 4473.2824) (11515.9695 4473.2824) (11638.229 4473.2824) (11671.6947 4473.2824)
      (11793.9542 4473.2824) (11827.4198 4473.2824) (11949.6794 4473.2824) (11983.145 4473.2824) (12022.9008 4473.2824)
    ))
    ; P1062 -- see feature_dimensions_mm.csv
    ("03_FRAMES_DOORS" 0 (
      (11723.7557 5494.7176) (11705.6947 5489.0229) (11687.4198 5482.7481) (11665.9847 5475.3893) (11626.9466 5460.7634)
      (11588.9618 5445.145) (11552.3817 5428.5344) (11517.5725 5410.9313) (11484.9008 5392.3053) (11454.7176 5372.6565)
      (11427.374 5351.9847) (11403.2519 5330.2901) (11382.7176 5307.542) (11366.1069 5283.771) (11353.7863 5258.9466)
      (11346.1374 5233.0534) (11343.5115 5206.1069) (11343.5115 4473.2824)
    ))
    ; P1063 -- see feature_dimensions_mm.csv
    ("03_FRAMES_DOORS" 0 (
      (11343.5115 3832.0611) (11498.7939 3832.0611) (11499.6794 3832.0611) (11654.5191 3832.0611) (11655.4046 3832.0611)
      (11810.2443 3832.0611) (11811.1298 3832.0611) (11965.9695 3832.0611) (11966.855 3832.0611) (12022.9008 3832.0611)
    ))
    ; P1064 -- see feature_dimensions_mm.csv
    ("03_FRAMES_DOORS" 0 (
      (11867.2366 2061.0687) (11866.5649 2062.7481) (11851.7099 2093.542) (11834.7634 2123.3588) (11815.771 2152.0611)
      (11794.8244 2179.542) (11772.0 2205.6794) (11747.4198 2230.3511) (11721.1603 2253.4656) (11693.3588 2274.916)
      (11664.1374 2294.6107) (11633.5878 2312.458) (11601.8626 2328.3969) (11569.1145 2342.3511) (11535.4504 2354.2595)
      (11501.0229 2364.0763) (11466.0 2371.7557) (11456.0611 2373.2977) (11451.6031 2351.145)
    ))
    ; P1065 -- see feature_dimensions_mm.csv
    ("03_FRAMES_DOORS" 0 (
      (11516.8397 2423.1908) (11477.9237 2431.7252)
    ))
    ; P1066 -- see feature_dimensions_mm.csv
    ("03_FRAMES_DOORS" 0 (
      (11698.0611 2346.0) (11664.1221 2365.8473)
    ))
    ; P1067 -- see feature_dimensions_mm.csv
    ("03_FRAMES_DOORS" 0 (
      (12319.9542 5517.8015) (12296.7939 5524.0611) (12257.9542 5533.8168) (12220.229 5542.6107) (12183.9847 5550.4733)
      (12149.5878 5557.374) (12117.3893 5563.3435) (12087.771 5568.3969) (12061.0687 5572.5191) (12034.3664 5568.3969)
      (12004.7481 5563.3435) (11972.5496 5557.374) (11938.1527 5550.4733) (11901.9084 5542.6107) (11864.1832 5533.8168)
      (11825.3435 5524.0611) (11785.7405 5513.3435) (11763.0382 5506.7176) (11745.7405 5501.6641)
    ))
    ; P1068 -- see feature_dimensions_mm.csv
    ("03_FRAMES_DOORS" 0 (
      (11847.3282 656.4885) (11908.3969 656.4885)
    ))
    ; P1069 -- see feature_dimensions_mm.csv
    ("03_FRAMES_DOORS" 0 (
      (11908.3969 656.4885) (11908.3969 1865.0382) (11907.2214 1898.8244) (11903.6947 1932.4733) (11897.8321 1965.8321)
      (11889.6641 1998.7481) (11879.2214 2031.1145) (11877.6336 2035.0992)
    ))
    ; P1070 -- see feature_dimensions_mm.csv
    ("03_FRAMES_DOORS" 0 (
      (11908.3969 656.4885) (11923.6641 656.4885)
    ))
    ; P1071 -- see feature_dimensions_mm.csv
    ("03_FRAMES_DOORS" 0 (
      (11923.6641 656.4885) (12198.4733 656.4885)
    ))
    ; P1072 -- see feature_dimensions_mm.csv
    ("03_FRAMES_DOORS" 0 (
      (11923.6641 656.4885) (11923.6641 1862.5954) (11969.4656 1862.5954) (12000.0 1862.5954) (12198.4733 1862.5954)
    ))
    ; P1073 -- see feature_dimensions_mm.csv
    ("03_FRAMES_DOORS" 0 (
      (11963.5267 1947.6947) (11954.1985 1969.4656)
    ))
    ; P1074 -- see feature_dimensions_mm.csv
    ("03_FRAMES_DOORS" 0 (
      (11963.3588 5679.3893) (11969.0992 5679.3893)
    ))
    ; P1075 -- see feature_dimensions_mm.csv
    ("03_FRAMES_DOORS" 0 (
      (11969.4656 1868.7023) (11968.1527 1906.2443)
    ))
    ; P1076 -- see feature_dimensions_mm.csv
    ("03_FRAMES_DOORS" 0 (
      (11969.0992 5679.3893) (12153.0382 5679.3893)
    ))
    ; P1077 -- see feature_dimensions_mm.csv
    ("03_FRAMES_DOORS" 1 (
      (12022.9008 4473.2824) (12099.2366 4473.2824) (12099.2366 5557.2519) (12022.9008 5557.2519)
    ))
    ; P1078 -- see feature_dimensions_mm.csv
    ("03_FRAMES_DOORS" 0 (
      (12022.9008 3832.0611) (12045.8015 3832.0611) (12045.8015 4412.2137) (12022.9008 4412.2137)
    ))
    ; P1079 -- see feature_dimensions_mm.csv
    ("03_FRAMES_DOORS" 0 (
      (12022.9008 4412.2137) (12022.9008 3832.0611)
    ))
    ; P1080 -- see feature_dimensions_mm.csv
    ("03_FRAMES_DOORS" 0 (
      (12616.1374 4412.2137) (12562.4885 4412.2137) (12460.4122 4412.2137) (12406.7634 4412.2137) (12304.687 4412.2137)
      (12251.0382 4412.2137) (12148.9618 4412.2137) (12106.8702 4412.2137) (12099.2366 4412.2137)
    ))
    ; P1081 -- see feature_dimensions_mm.csv
    ("03_FRAMES_DOORS" 0 (
      (12099.2366 3832.0611) (12099.2366 4412.2137)
    ))
    ; P1082 -- see feature_dimensions_mm.csv
    ("03_FRAMES_DOORS" 0 (
      (12099.2366 4412.2137) (12076.3359 4412.2137) (12076.3359 3832.0611) (12099.2366 3832.0611)
    ))
    ; P1083 -- see feature_dimensions_mm.csv
    ("03_FRAMES_DOORS" 0 (
      (12099.2366 3832.0611) (12121.6947 3832.0611) (12122.5802 3832.0611) (12277.4198 3832.0611)
    ))
    ; P1084 -- see feature_dimensions_mm.csv
    ("03_FRAMES_DOORS" 0 (
      (12153.0382 5679.3893) (12158.7786 5679.3893)
    ))
    ; P1085 -- see feature_dimensions_mm.csv
    ("03_FRAMES_DOORS" 0 (
      (12885.4962 4473.2824) (12885.4962 5282.4427) (12882.4733 5312.7634) (12873.6794 5341.8779) (12859.542 5369.8168)
      (12840.458 5396.5649) (12816.855 5422.1374) (12789.145 5446.5496) (12757.7405 5469.8015) (12723.0534 5491.9084)
      (12685.5115 5512.8702) (12645.5115 5532.687) (12603.4962 5551.374) (12559.8473 5568.9313) (12515.0076 5585.374)
      (12469.374 5600.7176) (12423.3588 5614.9466) (12377.4046 5628.0916) (12331.9084 5640.1374) (12287.2672 5651.1145)
      (12243.9237 5661.0076) (12202.2901 5669.8473) (12162.7634 5677.6183) (12153.0382 5679.3893)
    ))
    ; P1086 -- see feature_dimensions_mm.csv
    ("03_FRAMES_DOORS" 0 (
      (12992.3664 4473.2824) (12992.3664 5374.0458) (12988.9466 5405.4809) (12979.0229 5435.6794) (12963.0382 5464.6565)
      (12941.4962 5492.3969) (12914.8244 5518.916) (12883.5267 5544.229) (12848.0458 5568.3511) (12808.8702 5591.2672)
      (12766.458 5613.0076) (12721.2824 5633.5573) (12673.8015 5652.9313) (12624.5038 5671.145) (12573.8473 5688.1985)
      (12522.3053 5704.1069) (12470.3359 5718.8702) (12418.4122 5732.5038) (12367.0076 5744.9924) (12316.5954 5756.3664)
      (12267.6336 5766.6412) (12220.5954 5775.8015) (12180.7176 5782.9924)
    ))
    ; P1087 -- see feature_dimensions_mm.csv
    ("03_FRAMES_DOORS" 0 (
      (12193.8321 2061.0687) (12262.4733 2061.0687)
    ))
    ; P1088 -- see feature_dimensions_mm.csv
    ("03_FRAMES_DOORS" 0 (
      (12299.6336 2300.2901) (12270.4733 2274.6107) (12243.145 2247.1908) (12217.8015 2218.1527) (12194.5191 2187.6183)
      (12173.4198 2155.7252) (12154.5802 2122.5954) (12138.0916 2088.3817) (12127.1603 2061.0687) (12193.8321 2061.0687)
    ))
    ; P1089 -- see feature_dimensions_mm.csv
    ("03_FRAMES_DOORS" 0 (
      (13251.9084 656.4885) (13251.9084 1865.0382) (13250.7328 1898.8244) (13247.2061 1932.4733) (13241.3435 1965.8321)
      (13233.1756 1998.7481) (13222.7328 2031.1145) (13210.0763 2062.7481) (13195.2214 2093.542) (13178.2748 2123.3588)
      (13159.2824 2152.0611) (13138.3359 2179.542) (13115.5115 2205.6794) (13090.9313 2230.3511) (13064.6718 2253.4656)
      (13036.8702 2274.916) (13007.6489 2294.6107) (12977.0992 2312.458) (12945.374 2328.3969) (12912.626 2342.3511)
      (12878.9618 2354.2595) (12844.5344 2364.0763) (12809.5115 2371.7557) (12799.5725 2373.2977) (12795.1145 2351.145)
      (12609.4656 2351.145) (12605.0076 2373.2977) (12595.0687 2371.7557) (12560.0458 2364.0763) (12525.6183 2354.2595)
      (12491.9542 2342.3511) (12459.2061 2328.3969) (12427.4809 2312.458) (12396.9313 2294.6107) (12367.7099 2274.916)
      (12339.9084 2253.4656) (12313.6489 2230.3511) (12289.0687 2205.6794) (12266.2443 2179.542) (12245.2977 2152.0611)
      (12226.3053 2123.3588) (12209.3588 2093.542) (12194.5038 2062.7481) (12193.8321 2061.0687)
    ))
    ; P1090 -- see feature_dimensions_mm.csv
    ("03_FRAMES_DOORS" 0 (
      (12198.4733 1862.5954) (12198.4733 656.4885)
    ))
    ; P1091 -- see feature_dimensions_mm.csv
    ("03_FRAMES_DOORS" 0 (
      (12247.2977 2028.0611) (12198.4733 1969.4656) (12198.4733 1862.5954)
    ))
    ; P1092 -- see feature_dimensions_mm.csv
    ("03_FRAMES_DOORS" 0 (
      (12198.4733 656.4885) (12213.7405 656.4885)
    ))
    ; P1093 -- see feature_dimensions_mm.csv
    ("03_FRAMES_DOORS" 0 (
      (12213.7405 656.4885) (13190.8397 656.4885)
    ))
    ; P1094 -- see feature_dimensions_mm.csv
    ("03_FRAMES_DOORS" 0 (
      (12247.2977 2028.0611) (12239.6641 2008.9924) (12230.3817 1980.229) (12223.1298 1950.9618) (12217.9237 1921.313)
      (12214.7939 1891.4046) (12213.7405 1861.374) (12213.7405 656.4885)
    ))
    ; P1095 -- see feature_dimensions_mm.csv
    ("03_FRAMES_DOORS" 0 (
      (12262.4733 2061.0687) (12274.8092 2061.0687) (12247.2977 2028.0611)
    ))
    ; P1096 -- see feature_dimensions_mm.csv
    ("03_FRAMES_DOORS" 0 (
      (13190.8397 656.4885) (13190.8397 1861.374) (13189.7863 1891.4046) (13186.6565 1921.313) (13181.4504 1950.9618)
      (13174.1985 1980.229) (13164.916 2008.9924) (13153.6489 2037.1145) (13140.458 2064.4885) (13125.3893 2090.9924)
      (13108.5038 2116.5191) (13089.8779 2140.9466) (13069.6031 2164.1679) (13047.7405 2186.1069) (13024.4122 2206.6412)
      (12999.6947 2225.7099) (12973.7099 2243.2214) (12946.5649 2259.084) (12918.3664 2273.2519) (12889.2519 2285.6489)
      (12859.3282 2296.2443) (12828.7328 2304.9618) (12797.6031 2311.7863) (12766.0611 2316.687) (12734.2443 2319.6336)
      (12702.2901 2320.6107) (12670.3359 2319.6336) (12638.5191 2316.687) (12606.9771 2311.7863) (12575.8473 2304.9618)
      (12545.2519 2296.2443) (12515.3282 2285.6489) (12486.2137 2273.2519) (12458.0153 2259.084) (12430.8702 2243.2214)
      (12404.8855 2225.7099) (12380.1679 2206.6412) (12356.8397 2186.1069) (12334.9771 2164.1679) (12314.7023 2140.9466)
      (12296.0763 2116.5191) (12279.1908 2090.9924) (12264.1221 2064.4885) (12262.4733 2061.0687)
    ))
    ; P1097 -- see feature_dimensions_mm.csv
    ("03_FRAMES_DOORS" 0 (
      (12278.3053 3832.0611) (12433.145 3832.0611)
    ))
    ; P1098 -- see feature_dimensions_mm.csv
    ("03_FRAMES_DOORS" 0 (
      (12363.0076 2346.0) (12330.5344 2324.1221)
    ))
    ; P1099 -- see feature_dimensions_mm.csv
    ("03_FRAMES_DOORS" 0 (
      (12376.3969 5501.6641) (12336.3969 5513.3435)
    ))
    ; P1100 -- see feature_dimensions_mm.csv
    ("03_FRAMES_DOORS" 0 (
      (12480.1527 5466.3969) (12456.1527 5475.3893) (12416.4427 5489.0229) (12380.9466 5500.229)
    ))
    ; P1101 -- see feature_dimensions_mm.csv
    ("03_FRAMES_DOORS" 0 (
      (12432.1832 2383.542) (12396.9466 2365.8473)
    ))
    ; P1102 -- see feature_dimensions_mm.csv
    ("03_FRAMES_DOORS" 0 (
      (12434.0305 3832.0611) (12588.8702 3832.0611)
    ))
    ; P1103 -- see feature_dimensions_mm.csv
    ("03_FRAMES_DOORS" 0 (
      (12582.3359 5422.1679) (12569.7557 5428.5344) (12533.1756 5445.145) (12518.9008 5451.0229) (12503.1145 5457.5115)
      (12496.2748 5460.3206) (12495.1908 5460.7634)
    ))
    ; P1104 -- see feature_dimensions_mm.csv
    ("03_FRAMES_DOORS" 0 (
      (12778.626 5180.9924) (12778.626 5206.1069) (12776.0 5233.0534) (12768.3511 5258.9466) (12756.0305 5283.771)
      (12751.3282 5290.5038) (12739.4198 5307.542) (12718.8855 5330.2901) (12709.1298 5339.0534) (12694.7634 5351.9847)
      (12667.4351 5372.6565) (12637.2366 5392.3053) (12607.4962 5409.2519)
    ))
    ; P1105 -- see feature_dimensions_mm.csv
    ("03_FRAMES_DOORS" 0 (
      (12778.626 5055.6336) (12778.626 5170.6718)
    ))
    ; P1106 -- see feature_dimensions_mm.csv
    ("03_FRAMES_DOORS" 0 (
      (12778.626 5027.9237) (12778.626 5044.8855)
    ))
    ; P1107 -- see feature_dimensions_mm.csv
    ("03_FRAMES_DOORS" 0 (
      (12778.626 4995.3282) (12778.626 5012.2901)
    ))
    ; P1108 -- see feature_dimensions_mm.csv
    ("03_FRAMES_DOORS" 0 (
      (12778.626 4744.1832) (12778.626 4859.2214) (12778.626 4869.542) (12778.626 4984.5649)
    ))
    ; P1109 -- see feature_dimensions_mm.csv
    ("03_FRAMES_DOORS" 0 (
      (12778.626 4716.4733) (12778.626 4733.4351)
    ))
    ; P1110 -- see feature_dimensions_mm.csv
    ("03_FRAMES_DOORS" 0 (
      (12778.626 4683.8779) (12778.626 4700.8397)
    ))
    ; P1111 -- see feature_dimensions_mm.csv
    ("03_FRAMES_DOORS" 0 (
      (12778.626 4558.0916) (12778.626 4673.1145)
    ))
    ; P1112 -- see feature_dimensions_mm.csv
    ("03_FRAMES_DOORS" 0 (
      (12778.626 4473.2824) (12778.626 4547.771)
    ))
    ; P1113 -- see feature_dimensions_mm.csv
    ("03_FRAMES_DOORS" 0 (
      (12778.626 3935.1908) (12778.626 4050.2137) (12778.626 4060.9771) (12778.626 4077.9389) (12778.626 4093.5725)
      (12778.626 4110.5344) (12778.626 4121.2824) (12778.626 4236.3206) (12778.626 4246.6412) (12778.626 4361.6641)
      (12778.626 4372.4275) (12778.626 4389.3893) (12778.626 4405.0229) (12778.626 4412.2137)
    ))
    ; P1114 -- see feature_dimensions_mm.csv
    ("03_FRAMES_DOORS" 0 (
      (12778.626 3832.0611) (12778.626 3924.8702)
    ))
    ; P1115 -- see feature_dimensions_mm.csv
    ("03_FRAMES_DOORS" 0 (
      (12860.3511 2423.1908) (12821.4351 2431.7252)
    ))
    ; P1116 -- see feature_dimensions_mm.csv
    ("03_FRAMES_DOORS" 0 (
      (12885.4962 3832.0611) (12885.4962 4412.2137)
    ))
    ; P1117 -- see feature_dimensions_mm.csv
    ("03_FRAMES_DOORS" 0 (
      (12992.3664 3832.0611) (12992.3664 4412.2137)
    ))
    ; P1118 -- see feature_dimensions_mm.csv
    ("03_FRAMES_DOORS" 0 (
      (13041.5725 2346.0) (13007.6336 2365.8473)
    ))
    ; P1119 -- see feature_dimensions_mm.csv
    ("03_FRAMES_DOORS" 0 (
      (13190.8397 656.4885) (13251.9084 656.4885)
    ))
    ; P1120 -- see feature_dimensions_mm.csv
    ("03_FRAMES_DOORS" 0 (
      (13251.9084 656.4885) (13282.4427 656.4885)
    ))
    ; P1121 -- see feature_dimensions_mm.csv
    ("03_FRAMES_DOORS" 0 (
      (13293.3588 2012.4427) (13236.6412 2061.0687) (13277.4198 2061.0687)
    ))
    ; P1122 -- see feature_dimensions_mm.csv
    ("03_FRAMES_DOORS" 0 (
      (13282.4427 656.4885) (13557.2519 656.4885) (13557.2519 931.2977) (13557.2519 1282.4427) (13557.2519 1633.5878)
      (13557.2519 1862.5954) (13389.313 1862.5954) (13312.9771 1862.5954)
    ))
    ; P1123 -- see feature_dimensions_mm.csv
    ("03_FRAMES_DOORS" 0 (
      (13282.4427 656.4885) (13282.4427 1862.5954) (13312.9771 1862.5954)
    ))
    ; P1124 -- see feature_dimensions_mm.csv
    ("03_FRAMES_DOORS" 0 (
      (13312.9771 1862.5954) (13312.9771 1868.7023) (13311.6641 1906.2443) (13307.7557 1943.6336) (13301.2366 1980.687)
      (13300.2443 1984.7328)
    ))
    ; P1125 -- see feature_dimensions_mm.csv
    ("03_FRAMES_DOORS" 1 (
      (1206.1069 7465.6489) (1389.313 7465.6489) (1389.313 7114.5038) (1206.1069 7114.5038)
    ))
    ; P1126 -- see feature_dimensions_mm.csv
    ("03_FRAMES_DOORS" 1 (
      (1251.9084 9267.1756) (1358.7786 9267.1756) (1358.7786 8992.3664) (1251.9084 8992.3664)
    ))
    ; P1127 -- see feature_dimensions_mm.csv
    ("03_FRAMES_DOORS" 1 (
      (1473.2824 1847.3282) (1490.0763 1847.3282) (1490.0763 671.7557) (1473.2824 671.7557)
    ))
    ; P1128 -- see feature_dimensions_mm.csv
    ("03_FRAMES_DOORS" 1 (
      (1511.4504 1847.3282) (1528.2443 1847.3282) (1528.2443 671.7557) (1511.4504 671.7557)
    ))
    ; P1129 -- see feature_dimensions_mm.csv
    ("03_FRAMES_DOORS" 1 (
      (1549.6183 1847.3282) (1566.4122 1847.3282) (1566.4122 671.7557) (1549.6183 671.7557)
    ))
    ; P1130 -- see feature_dimensions_mm.csv
    ("03_FRAMES_DOORS" 1 (
      (1587.7863 1847.3282) (1604.5802 1847.3282) (1604.5802 671.7557) (1587.7863 671.7557)
    ))
    ; P1131 -- see feature_dimensions_mm.csv
    ("03_FRAMES_DOORS" 1 (
      (1625.9542 1847.3282) (1642.7481 1847.3282) (1642.7481 671.7557) (1625.9542 671.7557)
    ))
    ; P1132 -- see feature_dimensions_mm.csv
    ("03_FRAMES_DOORS" 1 (
      (1664.1221 1847.3282) (1680.916 1847.3282) (1680.916 671.7557) (1664.1221 671.7557)
    ))
    ; P1133 -- see feature_dimensions_mm.csv
    ("03_FRAMES_DOORS" 1 (
      (1694.6565 9312.9771) (1893.1298 9312.9771) (1893.1298 9145.0382) (1893.1298 9038.1679) (1893.1298 8946.5649)
      (1694.6565 8946.5649) (1694.6565 9038.1679) (1694.6565 9145.0382)
    ))
    ; P1134 -- see feature_dimensions_mm.csv
    ("03_FRAMES_DOORS" 1 (
      (1694.6565 7465.6489) (1877.8626 7465.6489) (1877.8626 7114.5038) (1694.6565 7114.5038)
    ))
    ; P1135 -- see feature_dimensions_mm.csv
    ("03_FRAMES_DOORS" 1 (
      (1740.458 9267.1756) (1847.3282 9267.1756) (1847.3282 8992.3664) (1740.458 8992.3664)
    ))
    ; P1136 -- see feature_dimensions_mm.csv
    ("03_FRAMES_DOORS" 1 (
      (2167.9389 9312.9771) (2366.4122 9312.9771) (2366.4122 9145.0382) (2366.4122 8946.5649) (2188.5496 8946.5649)
      (2167.9389 8946.5649) (2167.9389 9038.1679) (2167.9389 9145.0382)
    ))
    ; P1137 -- see feature_dimensions_mm.csv
    ("03_FRAMES_DOORS" 1 (
      (2167.9389 7465.6489) (2351.145 7465.6489) (2351.145 7114.5038) (2167.9389 7114.5038)
    ))
    ; P1138 -- see feature_dimensions_mm.csv
    ("03_FRAMES_DOORS" 1 (
      (2213.7405 9267.1756) (2320.6107 9267.1756) (2320.6107 8992.3664) (2213.7405 8992.3664)
    ))
    ; P1139 -- see feature_dimensions_mm.csv
    ("03_FRAMES_DOORS" 1 (
      (2656.4885 7465.6489) (2839.6947 7465.6489) (2839.6947 7114.5038) (2656.4885 7114.5038)
    ))
    ; P1140 -- see feature_dimensions_mm.csv
    ("03_FRAMES_DOORS" 1 (
      (2687.0229 9267.1756) (2793.8931 9267.1756) (2793.8931 8992.3664) (2687.0229 8992.3664)
    ))
    ; P1141 -- see feature_dimensions_mm.csv
    ("03_FRAMES_DOORS" 1 (
      (2862.5954 1847.3282) (2879.3893 1847.3282) (2879.3893 671.7557) (2862.5954 671.7557)
    ))
    ; P1142 -- see feature_dimensions_mm.csv
    ("03_FRAMES_DOORS" 1 (
      (2900.7634 1847.3282) (2917.5573 1847.3282) (2917.5573 671.7557) (2900.7634 671.7557)
    ))
    ; P1143 -- see feature_dimensions_mm.csv
    ("03_FRAMES_DOORS" 1 (
      (2938.9313 1847.3282) (2955.7252 1847.3282) (2955.7252 671.7557) (2938.9313 671.7557)
    ))
    ; P1144 -- see feature_dimensions_mm.csv
    ("03_FRAMES_DOORS" 1 (
      (2977.0992 1847.3282) (2993.8931 1847.3282) (2993.8931 671.7557) (2977.0992 671.7557)
    ))
    ; P1145 -- see feature_dimensions_mm.csv
    ("03_FRAMES_DOORS" 1 (
      (3015.2672 1847.3282) (3032.0611 1847.3282) (3032.0611 671.7557) (3015.2672 671.7557)
    ))
    ; P1146 -- see feature_dimensions_mm.csv
    ("03_FRAMES_DOORS" 1 (
      (3053.4351 1847.3282) (3070.229 1847.3282) (3070.229 671.7557) (3053.4351 671.7557)
    ))
    ; P1147 -- see feature_dimensions_mm.csv
    ("03_FRAMES_DOORS" 1 (
      (3129.771 7465.6489) (3312.9771 7465.6489) (3312.9771 7114.5038) (3129.771 7114.5038)
    ))
    ; P1148 -- see feature_dimensions_mm.csv
    ("03_FRAMES_DOORS" 1 (
      (3175.5725 9267.1756) (3282.4427 9267.1756) (3282.4427 8992.3664) (3175.5725 8992.3664)
    ))
    ; P1149 -- see feature_dimensions_mm.csv
    ("03_FRAMES_DOORS" 1 (
      (3389.313 1938.9313) (3389.9542 1956.9008) (3391.8626 1974.7939) (3395.0382 1992.5496) (3399.4504 2010.0611)
      (3405.1145 2027.2672) (3411.9695 2044.0916) (3420.0153 2060.4733) (3429.2061 2076.3359) (3439.4809 2091.6031)
      (3450.8397 2106.229) (3463.1908 2120.1221) (3476.5038 2133.2519) (3490.7328 2145.542) (3505.7863 2156.9466)
      (3521.6183 2167.4198) (3538.1679 2176.916) (3555.3435 2185.4046) (3573.0992 2192.8244) (3591.3282 2199.1603)
      (3609.9695 2204.3817) (3628.9466 2208.458) (3648.1679 2211.3893) (3667.5573 2213.145) (3687.0229 2213.7405)
      (3706.4885 2213.145) (3725.8779 2211.3893) (3745.0992 2208.458) (3764.0763 2204.3817) (3782.7176 2199.1603)
      (3800.9466 2192.8244) (3818.7023 2185.4046) (3835.8779 2176.916) (3852.4275 2167.4198) (3868.2595 2156.9466)
      (3883.313 2145.542) (3897.542 2133.2519) (3910.855 2120.1221) (3923.2061 2106.229) (3934.5649 2091.6031)
      (3944.855 2076.3359) (3954.0305 2060.4733) (3962.0763 2044.0916) (3968.9313 2027.2672) (3974.5954 2010.0611)
      (3979.0076 1992.5496) (3982.1832 1974.7939) (3984.0916 1956.9008) (3984.7328 1938.9313) (3984.7328 1435.1145)
      (3389.313 1435.1145)
    ))
    ; P1150 -- see feature_dimensions_mm.csv
    ("03_FRAMES_DOORS" 1 (
      (3389.313 1282.4427) (3984.7328 1282.4427) (3984.7328 610.687) (3389.313 610.687)
    ))
    ; P1151 -- see feature_dimensions_mm.csv
    ("03_FRAMES_DOORS" 1 (
      (3465.6489 1908.3969) (3466.1221 1922.3817) (3467.542 1936.2901) (3469.9084 1950.0916) (3473.1908 1963.7099)
      (3477.4046 1977.0992) (3482.5038 1990.1985) (3488.4733 2002.9313) (3495.313 2015.2672) (3502.9618 2027.145)
      (3511.3893 2038.5191) (3520.5802 2049.3282) (3530.4885 2059.5267) (3541.0534 2069.0992) (3552.2595 2077.9695)
      (3564.0305 2086.1221) (3576.3359 2093.4962) (3589.1145 2100.0916) (3602.3053 2105.8626) (3615.8626 2110.7939)
      (3629.7252 2114.855) (3643.8321 2118.0305) (3658.1221 2120.3053) (3672.5496 2121.6794) (3687.0229 2122.1374)
      (3701.4962 2121.6794) (3715.9237 2120.3053) (3730.2137 2118.0305) (3744.3206 2114.855) (3758.1832 2110.7939)
      (3771.7405 2105.8626) (3784.9313 2100.0916) (3797.7099 2093.4962) (3810.0153 2086.1221) (3821.7863 2077.9695)
      (3832.9924 2069.0992) (3843.5573 2059.5267) (3853.4656 2049.3282) (3862.6565 2038.5191) (3871.084 2027.145)
      (3878.7328 2015.2672) (3885.5725 2002.9313) (3891.542 1990.1985) (3896.6412 1977.0992) (3900.855 1963.7099)
      (3904.1374 1950.0916) (3906.5038 1936.2901) (3907.9237 1922.3817) (3908.3969 1908.3969) (3908.3969 1511.4504)
      (3465.6489 1511.4504)
    ))
    ; P1152 -- see feature_dimensions_mm.csv
    ("03_FRAMES_DOORS" 1 (
      (3465.6489 1206.1069) (3908.3969 1206.1069) (3908.3969 687.0229) (3465.6489 687.0229)
    ))
    ; P1153 -- see feature_dimensions_mm.csv
    ("03_FRAMES_DOORS" 1 (
      (3618.3206 7465.6489) (3801.5267 7465.6489) (3801.5267 7114.5038) (3618.3206 7114.5038)
    ))
    ; P1154 -- see feature_dimensions_mm.csv
    ("03_FRAMES_DOORS" 1 (
      (3664.1221 9267.1756) (3770.9924 9267.1756) (3770.9924 8992.3664) (3664.1221 8992.3664)
    ))
    ; P1155 -- see feature_dimensions_mm.csv
    ("03_FRAMES_DOORS" 1 (
      (4091.6031 7465.6489) (4274.8092 7465.6489) (4274.8092 7114.5038) (4091.6031 7114.5038)
    ))
    ; P1156 -- see feature_dimensions_mm.csv
    ("03_FRAMES_DOORS" 1 (
      (4282.4427 1847.3282) (4299.2366 1847.3282) (4299.2366 671.7557) (4282.4427 671.7557)
    ))
    ; P1157 -- see feature_dimensions_mm.csv
    ("03_FRAMES_DOORS" 1 (
      (4320.6107 1847.3282) (4337.4046 1847.3282) (4337.4046 671.7557) (4320.6107 671.7557)
    ))
    ; P1158 -- see feature_dimensions_mm.csv
    ("03_FRAMES_DOORS" 1 (
      (4358.7786 1847.3282) (4375.5725 1847.3282) (4375.5725 671.7557) (4358.7786 671.7557)
    ))
    ; P1159 -- see feature_dimensions_mm.csv
    ("03_FRAMES_DOORS" 1 (
      (4396.9466 1847.3282) (4413.7405 1847.3282) (4413.7405 671.7557) (4396.9466 671.7557)
    ))
    ; P1160 -- see feature_dimensions_mm.csv
    ("03_FRAMES_DOORS" 1 (
      (4435.1145 1847.3282) (4451.9084 1847.3282) (4451.9084 671.7557) (4435.1145 671.7557)
    ))
    ; P1161 -- see feature_dimensions_mm.csv
    ("03_FRAMES_DOORS" 1 (
      (4473.2824 1847.3282) (4490.0763 1847.3282) (4490.0763 671.7557) (4473.2824 671.7557)
    ))
    ; P1162 -- see feature_dimensions_mm.csv
    ("03_FRAMES_DOORS" 1 (
      (4580.1527 7465.6489) (4763.3588 7465.6489) (4763.3588 7114.5038) (4580.1527 7114.5038)
    ))
    ; P1163 -- see feature_dimensions_mm.csv
    ("03_FRAMES_DOORS" 1 (
      (5297.7099 5297.7099) (5298.5038 5324.6718) (5300.916 5351.5115) (5304.9008 5378.1221) (5310.458 5404.3969)
      (5317.5573 5430.2137) (5326.1832 5455.4504) (5336.2901 5480.0305) (5347.8168 5503.8168) (5360.7481 5526.7176)
      (5375.0076 5548.6565) (5390.5344 5569.4962) (5407.2672 5589.1908) (5425.1298 5607.6336) (5444.0458 5624.7481)
      (5463.9542 5640.458) (5484.7328 5654.7023) (5506.3206 5667.4198) (5528.6107 5678.5496) (5551.5267 5688.0458)
      (5574.9466 5695.8779) (5598.7786 5702.0) (5622.9313 5706.3969) (5647.2977 5709.0382) (5671.7557 5709.9237)
      (5696.2137 5709.0382) (5720.5802 5706.3969) (5744.7328 5702.0) (5768.5649 5695.8779) (5791.9847 5688.0458)
      (5814.9008 5678.5496) (5837.1908 5667.4198) (5858.7786 5654.7023) (5879.5573 5640.458) (5899.4656 5624.7481)
      (5918.3817 5607.6336) (5936.2443 5589.1908) (5952.9771 5569.4962) (5968.5038 5548.6565) (5982.7634 5526.7176)
      (5995.6947 5503.8168) (6007.2214 5480.0305) (6017.3282 5455.4504) (6025.9542 5430.2137) (6033.0534 5404.3969)
      (6038.6107 5378.1221) (6042.5954 5351.5115) (6045.0076 5324.6718) (6045.8015 5297.7099) (6045.8015 1129.771)
      (5297.7099 1129.771)
    ))
    ; P1164 -- see feature_dimensions_mm.csv
    ("03_FRAMES_DOORS" 1 (
      (5358.7786 5251.9084) (5359.4504 5276.8702) (5361.4504 5301.7252) (5364.7939 5326.3664) (5369.4504 5350.687)
      (5375.3893 5374.5954) (5382.5954 5397.9695) (5391.0534 5420.7176) (5400.7023 5442.7481) (5411.5267 5463.9542)
      (5423.4504 5484.2595) (5436.4427 5503.5725) (5450.4427 5521.8015) (5465.3893 5538.8702) (5481.2214 5554.7176)
      (5497.8779 5569.2672) (5515.2672 5582.458) (5533.3282 5594.229) (5551.9847 5604.5344) (5571.145 5613.3282)
      (5590.7481 5620.5802) (5610.7023 5626.2595) (5630.9008 5630.3206) (5651.2824 5632.7634) (5671.7557 5633.5878)
      (5692.229 5632.7634) (5712.6107 5630.3206) (5732.8092 5626.2595) (5752.7634 5620.5802) (5772.3664 5613.3282)
      (5791.5267 5604.5344) (5810.1832 5594.229) (5828.2443 5582.458) (5845.6336 5569.2672) (5862.2901 5554.7176)
      (5878.1221 5538.8702) (5893.0687 5521.8015) (5907.0687 5503.5725) (5920.0611 5484.2595) (5931.9847 5463.9542)
      (5942.8092 5442.7481) (5952.458 5420.7176) (5960.916 5397.9695) (5968.1221 5374.5954) (5974.0611 5350.687)
      (5978.7176 5326.3664) (5982.0611 5301.7252) (5984.0611 5276.8702) (5984.7328 5251.9084) (5984.7328 1206.1069)
      (5358.7786 1206.1069)
    ))
    ; P1165 -- see feature_dimensions_mm.csv
    ("03_FRAMES_DOORS" 1 (
      (6335.8779 5297.7099) (6337.0229 5324.6718) (6340.4427 5351.5115) (6346.1527 5378.1221) (6354.0916 5404.3969)
      (6364.229 5430.2137) (6376.5496 5455.4504) (6390.9771 5480.0305) (6407.4656 5503.8168) (6425.9389 5526.7176)
      (6446.3053 5548.6565) (6468.4885 5569.4962) (6492.3817 5589.1908) (6517.9084 5607.6336) (6544.9313 5624.7481)
      (6573.3588 5640.458) (6603.0534 5654.7023) (6633.8931 5667.4198) (6665.7405 5678.5496) (6698.4733 5688.0458)
      (6731.9237 5695.8779) (6765.9847 5702.0) (6800.4885 5706.3969) (6835.2824 5709.0382) (6870.229 5709.9237)
      (6905.1756 5709.0382) (6939.9695 5706.3969) (6974.4733 5702.0) (7008.5344 5695.8779) (7041.9847 5688.0458)
      (7074.7176 5678.5496) (7106.5649 5667.4198) (7137.4046 5654.7023) (7167.0992 5640.458) (7195.5267 5624.7481)
      (7222.5496 5607.6336) (7248.0763 5589.1908) (7271.9695 5569.4962) (7294.1527 5548.6565) (7314.5191 5526.7176)
      (7332.9924 5503.8168) (7349.4809 5480.0305) (7363.9084 5455.4504) (7376.229 5430.2137) (7386.3664 5404.3969)
      (7394.3053 5378.1221) (7400.0153 5351.5115) (7403.4351 5324.6718) (7404.5802 5297.7099) (7404.5802 1129.771)
      (6335.8779 1129.771)
    ))
    ; P1166 -- see feature_dimensions_mm.csv
    ("03_FRAMES_DOORS" 1 (
      (6396.9466 5251.9084) (6397.9542 5276.8702) (6400.9924 5301.7252) (6406.0458 5326.3664) (6413.0687 5350.687)
      (6422.0611 5374.5954) (6432.9771 5397.9695) (6445.7557 5420.7176) (6460.3511 5442.7481) (6476.7023 5463.9542)
      (6494.7481 5484.2595) (6514.3969 5503.5725) (6535.5725 5521.8015) (6558.1679 5538.8702) (6582.1069 5554.7176)
      (6607.2824 5569.2672) (6633.5878 5582.458) (6660.9008 5594.229) (6689.1145 5604.5344) (6718.0916 5613.3282)
      (6747.7405 5620.5802) (6777.8931 5626.2595) (6808.458 5630.3206) (6839.2824 5632.7634) (6870.229 5633.5878)
      (6901.1908 5632.7634) (6932.0 5630.3206) (6962.5649 5626.2595) (6992.7176 5620.5802) (7022.3664 5613.3282)
      (7051.3435 5604.5344) (7079.5573 5594.229) (7106.8702 5582.458) (7133.1756 5569.2672) (7158.3511 5554.7176)
      (7182.2901 5538.8702) (7204.8855 5521.8015) (7226.0611 5503.5725) (7245.7099 5484.2595) (7263.7557 5463.9542)
      (7280.1069 5442.7481) (7294.7023 5420.7176) (7307.4809 5397.9695) (7318.3969 5374.5954) (7327.3893 5350.687)
      (7334.4122 5326.3664) (7339.4656 5301.7252) (7342.5038 5276.8702) (7343.5115 5251.9084) (7343.5115 1206.1069)
      (6396.9466 1206.1069)
    ))
    ; P1167 -- see feature_dimensions_mm.csv
    ("03_FRAMES_DOORS" 1 (
      (7694.6565 5297.7099) (7695.4504 5324.6718) (7697.8626 5351.5115) (7701.8473 5378.1221) (7707.4046 5404.3969)
      (7714.5038 5430.2137) (7723.1298 5455.4504) (7733.2366 5480.0305) (7744.7634 5503.8168) (7757.6947 5526.7176)
      (7771.9542 5548.6565) (7787.4809 5569.4962) (7804.2137 5589.1908) (7822.0763 5607.6336) (7840.9924 5624.7481)
      (7860.9008 5640.458) (7881.6794 5654.7023) (7903.2672 5667.4198) (7925.5573 5678.5496) (7948.4733 5688.0458)
      (7971.8931 5695.8779) (7995.7252 5702.0) (8019.8779 5706.3969) (8044.2443 5709.0382) (8068.7023 5709.9237)
      (8093.1603 5709.0382) (8117.5267 5706.3969) (8141.6794 5702.0) (8165.5115 5695.8779) (8188.9313 5688.0458)
      (8211.8473 5678.5496) (8234.1374 5667.4198) (8255.7252 5654.7023) (8276.5038 5640.458) (8296.4122 5624.7481)
      (8315.3282 5607.6336) (8333.1908 5589.1908) (8349.9237 5569.4962) (8365.4504 5548.6565) (8379.7099 5526.7176)
      (8392.6412 5503.8168) (8404.1679 5480.0305) (8414.2748 5455.4504) (8422.9008 5430.2137) (8430.0 5404.3969)
      (8435.5573 5378.1221) (8439.542 5351.5115) (8441.9542 5324.6718) (8442.7481 5297.7099) (8442.7481 1129.771)
      (7694.6565 1129.771)
    ))
    ; P1168 -- see feature_dimensions_mm.csv
    ("03_FRAMES_DOORS" 1 (
      (7755.7252 5251.9084) (7756.3969 5276.8702) (7758.3969 5301.7252) (7761.7405 5326.3664) (7766.3969 5350.687)
      (7772.3359 5374.5954) (7779.542 5397.9695) (7788.0 5420.7176) (7797.6489 5442.7481) (7808.4733 5463.9542)
      (7820.3969 5484.2595) (7833.3893 5503.5725) (7847.3893 5521.8015) (7862.3359 5538.8702) (7878.1679 5554.7176)
      (7894.8244 5569.2672) (7912.2137 5582.458) (7930.2748 5594.229) (7948.9313 5604.5344) (7968.0916 5613.3282)
      (7987.6947 5620.5802) (8007.6489 5626.2595) (8027.8473 5630.3206) (8048.229 5632.7634) (8068.7023 5633.5878)
      (8089.1756 5632.7634) (8109.5573 5630.3206) (8129.7557 5626.2595) (8149.7099 5620.5802) (8169.313 5613.3282)
      (8188.4733 5604.5344) (8207.1298 5594.229) (8225.1908 5582.458) (8242.5802 5569.2672) (8259.2366 5554.7176)
      (8275.0687 5538.8702) (8290.0153 5521.8015) (8304.0153 5503.5725) (8317.0076 5484.2595) (8328.9313 5463.9542)
      (8339.7557 5442.7481) (8349.4046 5420.7176) (8357.8626 5397.9695) (8365.0687 5374.5954) (8371.0076 5350.687)
      (8375.6641 5326.3664) (8379.0076 5301.7252) (8381.0076 5276.8702) (8381.6794 5251.9084) (8381.6794 1206.1069)
      (7755.7252 1206.1069)
    ))
    ; P1169 -- see feature_dimensions_mm.csv
    ("03_FRAMES_DOORS" 1 (
      (8992.3664 7480.916) (8992.3664 7114.5038) (9175.5725 7114.5038) (9175.5725 7480.916)
    ))
    ; P1170 -- see feature_dimensions_mm.csv
    ("03_FRAMES_DOORS" 1 (
      (9022.9008 1938.9313) (9023.9084 1966.8855) (9026.9466 1994.7328) (9032.0 2022.3359) (9039.0229 2049.5725)
      (9048.0153 2076.3359) (9058.9313 2102.5191) (9071.7099 2128.0) (9086.3053 2152.6718) (9102.6565 2176.4275)
      (9120.7023 2199.1603) (9140.3511 2220.7939) (9161.5267 2241.2061) (9184.1221 2260.3359) (9208.0611 2278.0763)
      (9233.2366 2294.3664) (9259.542 2309.145) (9286.855 2322.3206) (9315.0687 2333.8779) (9344.0458 2343.7252)
      (9373.6947 2351.8473) (9403.8473 2358.1985) (9434.4122 2362.7481) (9465.2366 2365.4962) (9496.1832 2366.4122)
      (9527.145 2365.4962) (9557.9542 2362.7481) (9588.5191 2358.1985) (9618.6718 2351.8473) (9648.3206 2343.7252)
      (9677.2977 2333.8779) (9705.5115 2322.3206) (9732.8244 2309.145) (9759.1298 2294.3664) (9784.3053 2278.0763)
      (9808.2443 2260.3359) (9830.8397 2241.2061) (9852.0153 2220.7939) (9871.6641 2199.1603) (9889.7099 2176.4275)
      (9906.0611 2152.6718) (9920.6565 2128.0) (9933.4351 2102.5191) (9944.3511 2076.3359) (9953.3435 2049.5725)
      (9960.3664 2022.3359) (9965.4198 1994.7328) (9968.458 1966.8855) (9969.4656 1938.9313) (9969.4656 427.4809)
      (9022.9008 427.4809)
    ))
    ; P1171 -- see feature_dimensions_mm.csv
    ("03_FRAMES_DOORS" 1 (
      (9099.2366 1908.3969) (9100.0916 1932.3664) (9102.626 1956.229) (9106.8702 1979.8779) (9112.7634 2003.2366)
      (9120.3053 2026.1832) (9129.4504 2048.6107) (9140.1679 2070.458) (9152.4122 2091.6031) (9166.1374 2111.9695)
      (9181.2672 2131.4504) (9197.7405 2149.9847) (9215.4962 2167.4962) (9234.458 2183.8779) (9254.5344 2199.084)
      (9275.6489 2213.0534) (9297.7099 2225.7252) (9320.6107 2237.0229) (9344.2748 2246.916) (9368.5954 2255.3588)
      (9393.4504 2262.3206) (9418.7481 2267.771) (9444.3664 2271.6794) (9470.229 2274.0305) (9496.1832 2274.8092)
      (9522.1374 2274.0305) (9548.0 2271.6794) (9573.6183 2267.771) (9598.916 2262.3206) (9623.771 2255.3588)
      (9648.0916 2246.916) (9671.7557 2237.0229) (9694.6565 2225.7252) (9716.7176 2213.0534) (9737.8321 2199.084)
      (9757.9084 2183.8779) (9776.8702 2167.4962) (9794.626 2149.9847) (9811.0992 2131.4504) (9826.229 2111.9695)
      (9839.9542 2091.6031) (9852.1985 2070.458) (9862.916 2048.6107) (9872.0611 2026.1832) (9879.6031 2003.2366)
      (9885.4962 1979.8779) (9889.7405 1956.229) (9892.2748 1932.3664) (9893.1298 1908.3969) (9893.1298 473.2824)
      (9099.2366 473.2824)
    ))
    ; P1172 -- see feature_dimensions_mm.csv
    ("03_FRAMES_DOORS" 1 (
      (9206.1069 1282.4427) (9786.2595 1282.4427) (9786.2595 625.9542) (9206.1069 625.9542)
    ))
    ; P1173 -- see feature_dimensions_mm.csv
    ("03_FRAMES_DOORS" 1 (
      (9221.374 1862.5954) (9221.9695 1879.5725) (9223.7252 1896.4733) (9226.6565 1913.2366) (9230.7328 1929.771)
      (9235.9542 1946.0153) (9242.2901 1961.9237) (9249.7099 1977.3893) (9258.1985 1992.3664) (9267.6947 2006.7939)
      (9278.1679 2020.5954) (9289.5725 2033.7252) (9301.8626 2046.1221) (9314.9924 2057.7252) (9328.8855 2068.5038)
      (9343.5115 2078.3969) (9358.7786 2087.3588) (9374.6412 2095.374) (9391.0229 2102.3817) (9407.8473 2108.3664)
      (9425.0534 2113.2977) (9442.5649 2117.145) (9460.3206 2119.9237) (9478.2137 2121.5878) (9496.1832 2122.1374)
      (9514.1527 2121.5878) (9532.0458 2119.9237) (9549.8015 2117.145) (9567.313 2113.2977) (9584.5191 2108.3664)
      (9601.3435 2102.3817) (9617.7252 2095.374) (9633.5878 2087.3588) (9648.855 2078.3969) (9663.4809 2068.5038)
      (9677.374 2057.7252) (9690.5038 2046.1221) (9702.7939 2033.7252) (9714.1985 2020.5954) (9724.6718 2006.7939)
      (9734.1679 1992.3664) (9742.6565 1977.3893) (9750.0763 1961.9237) (9756.4122 1946.0153) (9761.6336 1929.771)
      (9765.7099 1913.2366) (9768.6412 1896.4733) (9770.3969 1879.5725) (9770.9924 1862.5954) (9770.9924 1435.1145)
      (9221.374 1435.1145)
    ))
    ; P1174 -- see feature_dimensions_mm.csv
    ("03_FRAMES_DOORS" 1 (
      (9282.4427 1832.0611) (9282.9008 1846.0458) (9284.2748 1859.9542) (9286.5496 1873.7557) (9289.7252 1887.374)
      (9293.7863 1900.7634) (9298.7176 1913.8626) (9304.4885 1926.5954) (9311.084 1938.9313) (9318.458 1950.8092)
      (9326.6107 1962.1832) (9335.4809 1972.9924) (9345.0534 1983.1908) (9355.2519 1992.7634) (9366.0611 2001.6336)
      (9377.4351 2009.7863) (9389.313 2017.1603) (9401.6489 2023.7557) (9414.3817 2029.5267) (9427.4809 2034.458)
      (9440.8702 2038.5191) (9454.4885 2041.6947) (9468.2901 2043.9695) (9482.1985 2045.3435) (9496.1832 2045.8015)
      (9510.1679 2045.3435) (9524.0763 2043.9695) (9537.8779 2041.6947) (9551.4962 2038.5191) (9564.8855 2034.458)
      (9577.9847 2029.5267) (9590.7176 2023.7557) (9603.0534 2017.1603) (9614.9313 2009.7863) (9626.3053 2001.6336)
      (9637.1145 1992.7634) (9647.313 1983.1908) (9656.8855 1972.9924) (9665.7557 1962.1832) (9673.9084 1950.8092)
      (9681.2824 1938.9313) (9687.8779 1926.5954) (9693.6489 1913.8626) (9698.5802 1900.7634) (9702.6412 1887.374)
      (9705.8168 1873.7557) (9708.0916 1859.9542) (9709.4656 1846.0458) (9709.9237 1832.0611) (9709.9237 1511.4504)
      (9282.4427 1511.4504)
    ))
    ; P1175 -- see feature_dimensions_mm.csv
    ("03_FRAMES_DOORS" 1 (
      (9282.4427 1206.1069) (9709.9237 1206.1069) (9709.9237 702.2901) (9282.4427 702.2901)
    ))
    ; P1176 -- see feature_dimensions_mm.csv
    ("03_FRAMES_DOORS" 1 (
      (9404.5802 7480.916) (9404.5802 7114.5038) (9587.7863 7114.5038) (9587.7863 7480.916)
    ))
    ; P1177 -- see feature_dimensions_mm.csv
    ("03_FRAMES_DOORS" 1 (
      (9816.7939 7480.916) (9816.7939 7114.5038) (10000.0 7114.5038) (10000.0 7480.916)
    ))
    ; P1178 -- see feature_dimensions_mm.csv
    ("03_FRAMES_DOORS" 1 (
      (10519.084 7465.6489) (10702.2901 7465.6489) (10702.2901 7114.5038) (10519.084 7114.5038)
    ))
    ; P1179 -- see feature_dimensions_mm.csv
    ("03_FRAMES_DOORS" 1 (
      (10618.3206 1847.3282) (10635.1145 1847.3282) (10635.1145 671.7557) (10618.3206 671.7557)
    ))
    ; P1180 -- see feature_dimensions_mm.csv
    ("03_FRAMES_DOORS" 1 (
      (10656.4885 1847.3282) (10673.2824 1847.3282) (10673.2824 671.7557) (10656.4885 671.7557)
    ))
    ; P1181 -- see feature_dimensions_mm.csv
    ("03_FRAMES_DOORS" 1 (
      (10694.6565 1847.3282) (10711.4504 1847.3282) (10711.4504 671.7557) (10694.6565 671.7557)
    ))
    ; P1182 -- see feature_dimensions_mm.csv
    ("03_FRAMES_DOORS" 1 (
      (10732.8244 1847.3282) (10749.6183 1847.3282) (10749.6183 671.7557) (10732.8244 671.7557)
    ))
    ; P1183 -- see feature_dimensions_mm.csv
    ("03_FRAMES_DOORS" 1 (
      (10770.9924 1847.3282) (10787.7863 1847.3282) (10787.7863 671.7557) (10770.9924 671.7557)
    ))
    ; P1184 -- see feature_dimensions_mm.csv
    ("03_FRAMES_DOORS" 1 (
      (10809.1603 1847.3282) (10825.9542 1847.3282) (10825.9542 671.7557) (10809.1603 671.7557)
    ))
    ; P1185 -- see feature_dimensions_mm.csv
    ("03_FRAMES_DOORS" 1 (
      (11007.6336 7465.6489) (11190.8397 7465.6489) (11190.8397 7114.5038) (11007.6336 7114.5038)
    ))
    ; P1186 -- see feature_dimensions_mm.csv
    ("03_FRAMES_DOORS" 1 (
      (11496.1832 7465.6489) (11679.3893 7465.6489) (11679.3893 7114.5038) (11496.1832 7114.5038)
    ))
    ; P1187 -- see feature_dimensions_mm.csv
    ("03_FRAMES_DOORS" 1 (
      (11961.8321 1847.3282) (11978.626 1847.3282) (11978.626 671.7557) (11961.8321 671.7557)
    ))
    ; P1188 -- see feature_dimensions_mm.csv
    ("03_FRAMES_DOORS" 1 (
      (11984.7328 7465.6489) (12167.9389 7465.6489) (12167.9389 7114.5038) (11984.7328 7114.5038)
    ))
    ; P1189 -- see feature_dimensions_mm.csv
    ("03_FRAMES_DOORS" 1 (
      (12000.0 1847.3282) (12016.7939 1847.3282) (12016.7939 671.7557) (12000.0 671.7557)
    ))
    ; P1190 -- see feature_dimensions_mm.csv
    ("03_FRAMES_DOORS" 1 (
      (12038.1679 1847.3282) (12054.9618 1847.3282) (12054.9618 671.7557) (12038.1679 671.7557)
    ))
    ; P1191 -- see feature_dimensions_mm.csv
    ("03_FRAMES_DOORS" 1 (
      (12076.3359 1847.3282) (12093.1298 1847.3282) (12093.1298 671.7557) (12076.3359 671.7557)
    ))
    ; P1192 -- see feature_dimensions_mm.csv
    ("03_FRAMES_DOORS" 1 (
      (12114.5038 1847.3282) (12131.2977 1847.3282) (12131.2977 671.7557) (12114.5038 671.7557)
    ))
    ; P1193 -- see feature_dimensions_mm.csv
    ("03_FRAMES_DOORS" 1 (
      (12152.6718 1847.3282) (12169.4656 1847.3282) (12169.4656 671.7557) (12152.6718 671.7557)
    ))
    ; P1194 -- see feature_dimensions_mm.csv
    ("03_FRAMES_DOORS" 1 (
      (12412.2137 3099.2366) (12534.3511 3099.2366) (12534.3511 2961.8321) (12534.3511 2809.1603) (12412.2137 2809.1603)
      (12412.2137 2961.8321)
    ))
    ; P1195 -- see feature_dimensions_mm.csv
    ("03_FRAMES_DOORS" 1 (
      (12473.2824 7465.6489) (12656.4885 7465.6489) (12656.4885 7114.5038) (12473.2824 7114.5038)
    ))
    ; P1196 -- see feature_dimensions_mm.csv
    ("03_FRAMES_DOORS" 1 (
      (12702.2901 3099.2366) (12824.4275 3099.2366) (12824.4275 2961.8321) (12824.4275 2809.1603) (12702.2901 2809.1603)
      (12702.2901 2961.8321)
    ))
    ; P1197 -- see feature_dimensions_mm.csv
    ("03_FRAMES_DOORS" 1 (
      (12961.8321 7465.6489) (13145.0382 7465.6489) (13145.0382 7114.5038) (12961.8321 7114.5038)
    ))
    ; P1198 -- see feature_dimensions_mm.csv
    ("03_FRAMES_DOORS" 1 (
      (12992.3664 3099.2366) (13114.5038 3099.2366) (13114.5038 2961.8321) (13114.5038 2809.1603) (12992.3664 2809.1603)
      (12992.3664 2961.8321)
    ))
    ; P1199 -- see feature_dimensions_mm.csv
    ("03_FRAMES_DOORS" 1 (
      (13320.6107 1847.3282) (13337.4046 1847.3282) (13337.4046 671.7557) (13320.6107 671.7557)
    ))
    ; P1200 -- see feature_dimensions_mm.csv
    ("03_FRAMES_DOORS" 1 (
      (13358.7786 1847.3282) (13375.5725 1847.3282) (13375.5725 671.7557) (13358.7786 671.7557)
    ))
    ; P1201 -- see feature_dimensions_mm.csv
    ("03_FRAMES_DOORS" 1 (
      (13396.9466 1847.3282) (13413.7405 1847.3282) (13413.7405 671.7557) (13396.9466 671.7557)
    ))
    ; P1202 -- see feature_dimensions_mm.csv
    ("03_FRAMES_DOORS" 1 (
      (13435.1145 7465.6489) (13618.3206 7465.6489) (13618.3206 7114.5038) (13435.1145 7114.5038)
    ))
    ; P1203 -- see feature_dimensions_mm.csv
    ("03_FRAMES_DOORS" 1 (
      (13435.1145 1847.3282) (13451.9084 1847.3282) (13451.9084 671.7557) (13435.1145 671.7557)
    ))
    ; P1204 -- see feature_dimensions_mm.csv
    ("03_FRAMES_DOORS" 1 (
      (13473.2824 1847.3282) (13490.0763 1847.3282) (13490.0763 671.7557) (13473.2824 671.7557)
    ))
    ; P1205 -- see feature_dimensions_mm.csv
    ("03_FRAMES_DOORS" 1 (
      (13511.4504 1847.3282) (13528.2443 1847.3282) (13528.2443 671.7557) (13511.4504 671.7557)
    ))
    ; P1206 -- see feature_dimensions_mm.csv
    ("04_GLAZING_SHUTTERS" 0 (
      (213.7405 7007.6336) (213.7405 7221.374) (213.7405 7435.1145) (213.7405 7496.1832) (578.626 7496.1832)
      (900.7634 7496.1832) (900.7634 7435.1145) (900.7634 7221.374) (900.7634 7114.5038) (900.7634 7007.6336)
    ))
    ; P1207 -- see feature_dimensions_mm.csv
    ("04_GLAZING_SHUTTERS" 0 (
      (900.7634 5847.3282) (493.8931 5847.3282) (213.7405 5847.3282) (213.7405 5938.9313) (213.7405 6152.6718)
      (213.7405 6366.4122) (213.7405 6580.1527)
    ))
    ; P1208 -- see feature_dimensions_mm.csv
    ("04_GLAZING_SHUTTERS" 0 (
      (213.7405 5404.5802) (213.7405 5511.4504) (213.7405 5725.1908) (213.7405 5816.7939) (493.8931 5816.7939)
      (900.7634 5816.7939)
    ))
    ; P1209 -- see feature_dimensions_mm.csv
    ("04_GLAZING_SHUTTERS" 0 (
      (900.7634 5083.9695) (900.7634 4870.229) (900.7634 4763.3588) (900.7634 4656.4885) (900.7634 4549.6183)
      (900.7634 4442.7481) (900.7634 4229.0076) (900.7634 4167.9389) (861.0687 4167.9389) (437.4046 4167.9389)
      (213.7405 4167.9389) (213.7405 4229.0076) (213.7405 4442.7481) (213.7405 4656.4885) (213.7405 4870.229)
      (213.7405 5083.9695)
    ))
    ; P1210 -- see feature_dimensions_mm.csv
    ("04_GLAZING_SHUTTERS" 0 (
      (340.855 6357.1908) (526.7176 6229.0076) (486.8092 6198.1221)
    ))
    ; P1211 -- see feature_dimensions_mm.csv
    ("04_GLAZING_SHUTTERS" 0 (
      (340.855 6357.1908) (320.6107 6305.3435) (486.8092 6198.1221)
    ))
    ; P1212 -- see feature_dimensions_mm.csv
    ("04_GLAZING_SHUTTERS" 0 (
      (360.9618 6408.6412) (305.3435 6381.6794) (340.855 6357.1908)
    ))
    ; P1213 -- see feature_dimensions_mm.csv
    ("04_GLAZING_SHUTTERS" 0 (
      (360.9618 6408.6412) (340.855 6357.1908)
    ))
    ; P1214 -- see feature_dimensions_mm.csv
    ("04_GLAZING_SHUTTERS" 0 (
      (340.855 4677.8015) (526.7176 4549.6183) (486.8092 4518.7328)
    ))
    ; P1215 -- see feature_dimensions_mm.csv
    ("04_GLAZING_SHUTTERS" 0 (
      (340.855 4677.8015) (320.6107 4625.9542) (486.8092 4518.7328)
    ))
    ; P1216 -- see feature_dimensions_mm.csv
    ("04_GLAZING_SHUTTERS" 0 (
      (360.9618 4729.2519) (305.3435 4702.2901) (340.855 4677.8015)
    ))
    ; P1217 -- see feature_dimensions_mm.csv
    ("04_GLAZING_SHUTTERS" 0 (
      (360.9618 4729.2519) (340.855 4677.8015)
    ))
    ; P1218 -- see feature_dimensions_mm.csv
    ("04_GLAZING_SHUTTERS" 0 (
      (753.542 6408.6412) (603.0534 6793.8931) (824.4275 7236.6412) (824.4275 7419.8473) (290.0763 7419.8473)
      (290.0763 7236.6412) (511.4504 6793.8931) (360.9618 6408.6412)
    ))
    ; P1219 -- see feature_dimensions_mm.csv
    ("04_GLAZING_SHUTTERS" 0 (
      (753.542 6408.6412) (557.2519 6503.8168) (360.9618 6408.6412)
    ))
    ; P1220 -- see feature_dimensions_mm.csv
    ("04_GLAZING_SHUTTERS" 0 (
      (753.542 4729.2519) (603.0534 5114.5038) (824.4275 5557.2519) (824.4275 5740.458) (290.0763 5740.458)
      (290.0763 5557.2519) (511.4504 5114.5038) (360.9618 4729.2519)
    ))
    ; P1221 -- see feature_dimensions_mm.csv
    ("04_GLAZING_SHUTTERS" 0 (
      (753.542 4729.2519) (557.2519 4824.4275) (360.9618 4729.2519)
    ))
    ; P1222 -- see feature_dimensions_mm.csv
    ("04_GLAZING_SHUTTERS" 0 (
      (486.8092 6198.1221) (557.2519 6152.6718) (627.6947 6198.1221)
    ))
    ; P1223 -- see feature_dimensions_mm.csv
    ("04_GLAZING_SHUTTERS" 0 (
      (486.8092 6198.1221) (290.0763 6045.8015) (290.0763 5923.6641) (824.4275 5923.6641) (824.4275 6045.8015)
      (627.6947 6198.1221)
    ))
    ; P1224 -- see feature_dimensions_mm.csv
    ("04_GLAZING_SHUTTERS" 0 (
      (486.8092 4518.7328) (557.2519 4473.2824) (627.6947 4518.7328)
    ))
    ; P1225 -- see feature_dimensions_mm.csv
    ("04_GLAZING_SHUTTERS" 0 (
      (486.8092 4518.7328) (290.0763 4366.4122) (290.0763 4244.2748) (824.4275 4244.2748) (824.4275 4366.4122)
      (627.6947 4518.7328)
    ))
    ; P1226 -- see feature_dimensions_mm.csv
    ("04_GLAZING_SHUTTERS" 0 (
      (627.6947 6198.1221) (587.7863 6229.0076) (773.6489 6357.1908)
    ))
    ; P1227 -- see feature_dimensions_mm.csv
    ("04_GLAZING_SHUTTERS" 0 (
      (627.6947 6198.1221) (793.8931 6305.3435) (773.6489 6357.1908)
    ))
    ; P1228 -- see feature_dimensions_mm.csv
    ("04_GLAZING_SHUTTERS" 0 (
      (627.6947 4518.7328) (587.7863 4549.6183) (773.6489 4677.8015)
    ))
    ; P1229 -- see feature_dimensions_mm.csv
    ("04_GLAZING_SHUTTERS" 0 (
      (627.6947 4518.7328) (793.8931 4625.9542) (773.6489 4677.8015)
    ))
    ; P1230 -- see feature_dimensions_mm.csv
    ("04_GLAZING_SHUTTERS" 0 (
      (773.6489 6357.1908) (809.1603 6381.6794) (753.542 6408.6412)
    ))
    ; P1231 -- see feature_dimensions_mm.csv
    ("04_GLAZING_SHUTTERS" 0 (
      (773.6489 6357.1908) (753.542 6408.6412)
    ))
    ; P1232 -- see feature_dimensions_mm.csv
    ("04_GLAZING_SHUTTERS" 0 (
      (773.6489 4677.8015) (809.1603 4702.2901) (753.542 4729.2519)
    ))
    ; P1233 -- see feature_dimensions_mm.csv
    ("04_GLAZING_SHUTTERS" 0 (
      (773.6489 4677.8015) (753.542 4729.2519)
    ))
    ; P1234 -- see feature_dimensions_mm.csv
    ("04_GLAZING_SHUTTERS" 0 (
      (2732.8244 1099.2366) (1786.2595 1099.2366)
    ))
    ; P1235 -- see feature_dimensions_mm.csv
    ("04_GLAZING_SHUTTERS" 0 (
      (1786.2595 977.0992) (1786.2595 1099.2366)
    ))
    ; P1236 -- see feature_dimensions_mm.csv
    ("04_GLAZING_SHUTTERS" 0 (
      (1786.2595 1099.2366) (1786.2595 1221.374) (2732.8244 1221.374) (2732.8244 1099.2366)
    ))
    ; P1237 -- see feature_dimensions_mm.csv
    ("04_GLAZING_SHUTTERS" 0 (
      (2732.8244 977.0992) (1786.2595 977.0992)
    ))
    ; P1238 -- see feature_dimensions_mm.csv
    ("04_GLAZING_SHUTTERS" 0 (
      (1786.2595 961.8321) (1786.2595 977.0992)
    ))
    ; P1239 -- see feature_dimensions_mm.csv
    ("04_GLAZING_SHUTTERS" 0 (
      (1786.2595 961.8321) (2732.8244 961.8321)
    ))
    ; P1240 -- see feature_dimensions_mm.csv
    ("04_GLAZING_SHUTTERS" 0 (
      (1786.2595 839.6947) (1786.2595 961.8321)
    ))
    ; P1241 -- see feature_dimensions_mm.csv
    ("04_GLAZING_SHUTTERS" 0 (
      (2732.8244 839.6947) (1786.2595 839.6947)
    ))
    ; P1242 -- see feature_dimensions_mm.csv
    ("04_GLAZING_SHUTTERS" 0 (
      (1786.2595 824.4275) (1786.2595 839.6947)
    ))
    ; P1243 -- see feature_dimensions_mm.csv
    ("04_GLAZING_SHUTTERS" 0 (
      (1786.2595 824.4275) (2732.8244 824.4275)
    ))
    ; P1244 -- see feature_dimensions_mm.csv
    ("04_GLAZING_SHUTTERS" 0 (
      (1786.2595 702.2901) (1786.2595 824.4275)
    ))
    ; P1245 -- see feature_dimensions_mm.csv
    ("04_GLAZING_SHUTTERS" 0 (
      (2732.8244 702.2901) (1786.2595 702.2901)
    ))
    ; P1246 -- see feature_dimensions_mm.csv
    ("04_GLAZING_SHUTTERS" 0 (
      (2732.8244 702.2901) (2732.8244 671.7557) (1786.2595 671.7557) (1786.2595 702.2901)
    ))
    ; P1247 -- see feature_dimensions_mm.csv
    ("04_GLAZING_SHUTTERS" 0 (
      (2717.5573 1608.9618) (2717.5573 1236.6412) (1801.5267 1236.6412) (1801.5267 1609.5878) (1801.5267 1629.7099)
      (1801.5267 1844.2748) (1801.8015 1851.9542)
    ))
    ; P1248 -- see feature_dimensions_mm.csv
    ("04_GLAZING_SHUTTERS" 0 (
      (1802.5038 1872.2137) (1802.5038 1872.4275) (1805.4504 1900.4733) (1810.3206 1928.2748) (1817.1298 1955.7099)
      (1825.8321 1982.6718) (1836.3969 2009.0382) (1848.7634 2034.7023) (1862.8855 2059.542) (1878.7176 2083.4656)
      (1896.1679 2106.3664) (1915.1908 2128.1527) (1935.6794 2148.7023) (1957.5573 2167.9695) (1966.1527 2174.5954)
    ))
    ; P1249 -- see feature_dimensions_mm.csv
    ("04_GLAZING_SHUTTERS" 0 (
      (1982.5954 2187.0992) (2005.084 2202.2443) (2030.5344 2217.1298) (2056.9618 2230.4122) (2084.2748 2242.0305)
      (2112.3206 2251.9542) (2140.9924 2260.1374) (2170.1832 2266.5344) (2199.7557 2271.1298) (2229.5878 2273.8931)
      (2259.542 2274.8092) (2289.4962 2273.8931) (2319.3282 2271.1298) (2348.9008 2266.5344) (2378.0916 2260.1374)
      (2406.7634 2251.9542) (2434.8244 2242.0305) (2462.1221 2230.4122) (2488.5496 2217.1298) (2514.0 2202.2443)
      (2536.4885 2187.0992)
    ))
    ; P1250 -- see feature_dimensions_mm.csv
    ("04_GLAZING_SHUTTERS" 0 (
      (2552.9313 2174.5954) (2561.5267 2167.9695) (2583.4046 2148.7023) (2603.8931 2128.1527) (2622.916 2106.3664)
      (2640.3664 2083.4656) (2656.1985 2059.542) (2670.3206 2034.7023) (2682.687 2009.0382) (2693.2519 1982.6718)
      (2701.9542 1955.7099) (2708.7634 1928.2748) (2713.6336 1900.4733) (2716.5802 1872.4275) (2716.6107 1871.5725)
    ))
    ; P1251 -- see feature_dimensions_mm.csv
    ("04_GLAZING_SHUTTERS" 0 (
      (2717.3282 1851.0076) (2717.5573 1844.2748) (2717.5573 1628.7023)
    ))
    ; P1252 -- see feature_dimensions_mm.csv
    ("04_GLAZING_SHUTTERS" 0 (
      (2732.8244 1099.2366) (2732.8244 977.0992)
    ))
    ; P1253 -- see feature_dimensions_mm.csv
    ("04_GLAZING_SHUTTERS" 0 (
      (2732.8244 977.0992) (2732.8244 961.8321)
    ))
    ; P1254 -- see feature_dimensions_mm.csv
    ("04_GLAZING_SHUTTERS" 0 (
      (2732.8244 961.8321) (2732.8244 839.6947)
    ))
    ; P1255 -- see feature_dimensions_mm.csv
    ("04_GLAZING_SHUTTERS" 0 (
      (2732.8244 839.6947) (2732.8244 824.4275)
    ))
    ; P1256 -- see feature_dimensions_mm.csv
    ("04_GLAZING_SHUTTERS" 0 (
      (2732.8244 824.4275) (2732.8244 702.2901)
    ))
    ; P1257 -- see feature_dimensions_mm.csv
    ("04_GLAZING_SHUTTERS" 0 (
      (5435.1145 4519.084) (5923.6641 4519.084)
    ))
    ; P1258 -- see feature_dimensions_mm.csv
    ("04_GLAZING_SHUTTERS" 0 (
      (5435.1145 2366.4122) (5435.1145 4519.084)
    ))
    ; P1259 -- see feature_dimensions_mm.csv
    ("04_GLAZING_SHUTTERS" 0 (
      (5435.1145 4519.084) (5435.1145 5236.6412) (5436.0153 5260.2137) (5438.6107 5282.8702) (5442.8092 5304.5954)
      (5448.458 5325.4046) (5455.4504 5345.2977) (5463.6641 5364.2901) (5472.9618 5382.3664) (5483.2519 5399.5573)
      (5494.3664 5415.8626) (5506.2137 5431.2672) (5518.6718 5445.8015) (5531.6031 5459.4656) (5544.8855 5472.2595)
      (5558.4122 5484.1832) (5572.0458 5495.2519) (5585.6641 5505.4809) (5599.145 5514.855) (5612.3664 5523.3893)
      (5625.2061 5531.084) (5637.542 5537.9542) (5649.2519 5544.0) (5660.2137 5549.2366) (5670.3053 5553.6489)
      (5679.3893 5557.2519) (5688.4733 5553.6489) (5698.5649 5549.2366) (5709.5267 5544.0) (5721.2366 5537.9542)
      (5733.5725 5531.084) (5746.4122 5523.3893) (5759.6336 5514.855) (5773.1145 5505.4809) (5786.7328 5495.2519)
      (5800.3664 5484.1832) (5813.8931 5472.2595) (5827.1756 5459.4656) (5840.1069 5445.8015) (5852.5649 5431.2672)
      (5864.4122 5415.8626) (5875.5267 5399.5573) (5885.8168 5382.3664) (5895.1145 5364.2901) (5903.3282 5345.2977)
      (5910.3206 5325.4046) (5915.9695 5304.5954) (5920.1679 5282.8702) (5922.7634 5260.2137) (5923.6641 5236.6412)
      (5923.6641 4519.084)
    ))
    ; P1260 -- see feature_dimensions_mm.csv
    ("04_GLAZING_SHUTTERS" 0 (
      (5450.3817 2366.4122) (5435.1145 2366.4122)
    ))
    ; P1261 -- see feature_dimensions_mm.csv
    ("04_GLAZING_SHUTTERS" 0 (
      (5923.6641 2366.4122) (5923.6641 1236.6412) (5435.1145 1236.6412) (5435.1145 2366.4122)
    ))
    ; P1262 -- see feature_dimensions_mm.csv
    ("04_GLAZING_SHUTTERS" 0 (
      (5908.3969 2366.4122) (5450.3817 2366.4122)
    ))
    ; P1263 -- see feature_dimensions_mm.csv
    ("04_GLAZING_SHUTTERS" 0 (
      (5908.3969 2366.4122) (5908.3969 2355.7252) (5450.3817 2355.7252) (5450.3817 2366.4122)
    ))
    ; P1264 -- see feature_dimensions_mm.csv
    ("04_GLAZING_SHUTTERS" 0 (
      (5450.3817 2366.4122) (5450.3817 2427.4809) (5908.3969 2427.4809) (5908.3969 2366.4122)
    ))
    ; P1265 -- see feature_dimensions_mm.csv
    ("04_GLAZING_SHUTTERS" 0 (
      (5923.6641 2366.4122) (5908.3969 2366.4122)
    ))
    ; P1266 -- see feature_dimensions_mm.csv
    ("04_GLAZING_SHUTTERS" 0 (
      (5923.6641 4519.084) (5923.6641 2366.4122)
    ))
    ; P1267 -- see feature_dimensions_mm.csv
    ("04_GLAZING_SHUTTERS" 0 (
      (6412.2137 4519.084) (7328.2443 4519.084)
    ))
    ; P1268 -- see feature_dimensions_mm.csv
    ("04_GLAZING_SHUTTERS" 0 (
      (6412.2137 2366.4122) (6412.2137 4519.084)
    ))
    ; P1269 -- see feature_dimensions_mm.csv
    ("04_GLAZING_SHUTTERS" 0 (
      (6412.2137 4519.084) (6412.2137 5236.6412) (6413.8931 5260.2137) (6418.7786 5282.8702) (6426.6412 5304.5954)
      (6437.2366 5325.4046) (6450.3511 5345.2977) (6465.7405 5364.2901) (6483.1908 5382.3664) (6502.458 5399.5573)
      (6523.313 5415.8626) (6545.542 5431.2672) (6568.8855 5445.8015) (6593.1298 5459.4656) (6618.0458 5472.2595)
      (6643.3893 5484.1832) (6668.9466 5495.2519) (6694.4885 5505.4809) (6719.771 5514.855) (6744.5649 5523.3893)
      (6768.6412 5531.084) (6791.771 5537.9542) (6813.7252 5544.0) (6834.2748 5549.2366) (6853.1908 5553.6489)
      (6870.229 5557.2519) (6887.2672 5553.6489) (6906.1832 5549.2366) (6926.7328 5544.0) (6948.687 5537.9542)
      (6971.8168 5531.084) (6995.8931 5523.3893) (7020.687 5514.855) (7045.9695 5505.4809) (7071.5115 5495.2519)
      (7097.0687 5484.1832) (7122.4122 5472.2595) (7147.3282 5459.4656) (7171.5725 5445.8015) (7194.916 5431.2672)
      (7217.145 5415.8626) (7238.0 5399.5573) (7257.2672 5382.3664) (7274.7176 5364.2901) (7290.1069 5345.2977)
      (7303.2214 5325.4046) (7313.8168 5304.5954) (7321.6794 5282.8702) (7326.5649 5260.2137) (7328.2443 5236.6412)
      (7328.2443 4519.084)
    ))
    ; P1270 -- see feature_dimensions_mm.csv
    ("04_GLAZING_SHUTTERS" 0 (
      (6427.4809 2366.4122) (6412.2137 2366.4122)
    ))
    ; P1271 -- see feature_dimensions_mm.csv
    ("04_GLAZING_SHUTTERS" 0 (
      (7328.2443 2366.4122) (7328.2443 1236.6412) (6412.2137 1236.6412) (6412.2137 2366.4122)
    ))
    ; P1272 -- see feature_dimensions_mm.csv
    ("04_GLAZING_SHUTTERS" 0 (
      (7312.9771 2366.4122) (6427.4809 2366.4122)
    ))
    ; P1273 -- see feature_dimensions_mm.csv
    ("04_GLAZING_SHUTTERS" 0 (
      (7312.9771 2366.4122) (7312.9771 2355.7252) (6427.4809 2355.7252) (6427.4809 2366.4122)
    ))
    ; P1274 -- see feature_dimensions_mm.csv
    ("04_GLAZING_SHUTTERS" 0 (
      (6427.4809 2366.4122) (6427.4809 2427.4809) (7312.9771 2427.4809) (7312.9771 2366.4122)
    ))
    ; P1275 -- see feature_dimensions_mm.csv
    ("04_GLAZING_SHUTTERS" 0 (
      (6458.0153 1832.0611) (6656.4885 1832.0611)
    ))
    ; P1276 -- see feature_dimensions_mm.csv
    ("04_GLAZING_SHUTTERS" 0 (
      (6458.0153 1832.0611) (6458.0153 1282.4427) (6870.229 1282.4427)
    ))
    ; P1277 -- see feature_dimensions_mm.csv
    ("04_GLAZING_SHUTTERS" 0 (
      (6870.229 2305.3435) (6458.0153 2305.3435) (6458.0153 1832.0611)
    ))
    ; P1278 -- see feature_dimensions_mm.csv
    ("04_GLAZING_SHUTTERS" 0 (
      (6656.4885 1832.0611) (6870.229 1587.7863)
    ))
    ; P1279 -- see feature_dimensions_mm.csv
    ("04_GLAZING_SHUTTERS" 0 (
      (6870.229 2106.8702) (6656.4885 1832.0611)
    ))
    ; P1280 -- see feature_dimensions_mm.csv
    ("04_GLAZING_SHUTTERS" 0 (
      (7282.4427 1832.0611) (7282.4427 2305.3435) (6870.229 2305.3435)
    ))
    ; P1281 -- see feature_dimensions_mm.csv
    ("04_GLAZING_SHUTTERS" 0 (
      (6870.229 2106.8702) (6870.229 2305.3435)
    ))
    ; P1282 -- see feature_dimensions_mm.csv
    ("04_GLAZING_SHUTTERS" 0 (
      (7083.9695 1832.0611) (6870.229 2106.8702)
    ))
    ; P1283 -- see feature_dimensions_mm.csv
    ("04_GLAZING_SHUTTERS" 0 (
      (6870.229 1587.7863) (6870.229 1282.4427)
    ))
    ; P1284 -- see feature_dimensions_mm.csv
    ("04_GLAZING_SHUTTERS" 0 (
      (6870.229 1587.7863) (7083.9695 1832.0611)
    ))
    ; P1285 -- see feature_dimensions_mm.csv
    ("04_GLAZING_SHUTTERS" 0 (
      (6870.229 1282.4427) (7282.4427 1282.4427) (7282.4427 1832.0611)
    ))
    ; P1286 -- see feature_dimensions_mm.csv
    ("04_GLAZING_SHUTTERS" 0 (
      (7083.9695 1832.0611) (7282.4427 1832.0611)
    ))
    ; P1287 -- see feature_dimensions_mm.csv
    ("04_GLAZING_SHUTTERS" 0 (
      (7328.2443 2366.4122) (7312.9771 2366.4122)
    ))
    ; P1288 -- see feature_dimensions_mm.csv
    ("04_GLAZING_SHUTTERS" 0 (
      (7328.2443 4519.084) (7328.2443 2366.4122)
    ))
    ; P1289 -- see feature_dimensions_mm.csv
    ("04_GLAZING_SHUTTERS" 0 (
      (7832.0611 4519.084) (8305.3435 4519.084)
    ))
    ; P1290 -- see feature_dimensions_mm.csv
    ("04_GLAZING_SHUTTERS" 0 (
      (7832.0611 2366.4122) (7832.0611 4519.084)
    ))
    ; P1291 -- see feature_dimensions_mm.csv
    ("04_GLAZING_SHUTTERS" 0 (
      (7832.0611 4519.084) (7832.0611 5236.6412) (7832.9313 5260.2137) (7835.4504 5282.8702) (7839.5115 5304.5954)
      (7844.9924 5325.4046) (7851.771 5345.2977) (7859.7252 5364.2901) (7868.7328 5382.3664) (7878.687 5399.5573)
      (7889.4656 5415.8626) (7900.9466 5431.2672) (7913.0076 5445.8015) (7925.542 5459.4656) (7938.4122 5472.2595)
      (7951.5115 5484.1832) (7964.7023 5495.2519) (7977.9084 5505.4809) (7990.9618 5514.855) (8003.771 5523.3893)
      (8016.2137 5531.084) (8028.1679 5537.9542) (8039.5115 5544.0) (8050.1221 5549.2366) (8059.8931 5553.6489)
      (8068.7023 5557.2519) (8077.5115 5553.6489) (8087.2824 5549.2366) (8097.8931 5544.0) (8109.2366 5537.9542)
      (8121.1908 5531.084) (8133.6336 5523.3893) (8146.4427 5514.855) (8159.4962 5505.4809) (8172.7023 5495.2519)
      (8185.8931 5484.1832) (8198.9924 5472.2595) (8211.8779 5459.4656) (8224.3969 5445.8015) (8236.458 5431.2672)
      (8247.9389 5415.8626) (8258.7176 5399.5573) (8268.6718 5382.3664) (8277.6794 5364.2901) (8285.6336 5345.2977)
      (8292.4122 5325.4046) (8297.8931 5304.5954) (8301.9542 5282.8702) (8304.4733 5260.2137) (8305.3435 5236.6412)
      (8305.3435 4519.084)
    ))
    ; P1292 -- see feature_dimensions_mm.csv
    ("04_GLAZING_SHUTTERS" 0 (
      (7847.3282 2366.4122) (7832.0611 2366.4122)
    ))
    ; P1293 -- see feature_dimensions_mm.csv
    ("04_GLAZING_SHUTTERS" 0 (
      (8305.3435 2366.4122) (8305.3435 1236.6412) (7832.0611 1236.6412) (7832.0611 2366.4122)
    ))
    ; P1294 -- see feature_dimensions_mm.csv
    ("04_GLAZING_SHUTTERS" 0 (
      (8290.0763 2366.4122) (7847.3282 2366.4122)
    ))
    ; P1295 -- see feature_dimensions_mm.csv
    ("04_GLAZING_SHUTTERS" 0 (
      (8290.0763 2366.4122) (8290.0763 2355.7252) (7847.3282 2355.7252) (7847.3282 2366.4122)
    ))
    ; P1296 -- see feature_dimensions_mm.csv
    ("04_GLAZING_SHUTTERS" 0 (
      (7847.3282 2366.4122) (7847.3282 2427.4809) (8290.0763 2427.4809) (8290.0763 2366.4122)
    ))
    ; P1297 -- see feature_dimensions_mm.csv
    ("04_GLAZING_SHUTTERS" 0 (
      (8305.3435 2366.4122) (8290.0763 2366.4122)
    ))
    ; P1298 -- see feature_dimensions_mm.csv
    ("04_GLAZING_SHUTTERS" 0 (
      (8305.3435 4519.084) (8305.3435 2366.4122)
    ))
    ; P1299 -- see feature_dimensions_mm.csv
    ("04_GLAZING_SHUTTERS" 0 (
      (11832.0611 1099.2366) (10885.4962 1099.2366)
    ))
    ; P1300 -- see feature_dimensions_mm.csv
    ("04_GLAZING_SHUTTERS" 0 (
      (10885.4962 977.0992) (10885.4962 1099.2366)
    ))
    ; P1301 -- see feature_dimensions_mm.csv
    ("04_GLAZING_SHUTTERS" 0 (
      (10885.4962 1099.2366) (10885.4962 1221.374) (11832.0611 1221.374) (11832.0611 1099.2366)
    ))
    ; P1302 -- see feature_dimensions_mm.csv
    ("04_GLAZING_SHUTTERS" 0 (
      (11832.0611 977.0992) (10885.4962 977.0992)
    ))
    ; P1303 -- see feature_dimensions_mm.csv
    ("04_GLAZING_SHUTTERS" 0 (
      (10885.4962 961.8321) (10885.4962 977.0992)
    ))
    ; P1304 -- see feature_dimensions_mm.csv
    ("04_GLAZING_SHUTTERS" 0 (
      (10885.4962 961.8321) (11832.0611 961.8321)
    ))
    ; P1305 -- see feature_dimensions_mm.csv
    ("04_GLAZING_SHUTTERS" 0 (
      (10885.4962 839.6947) (10885.4962 961.8321)
    ))
    ; P1306 -- see feature_dimensions_mm.csv
    ("04_GLAZING_SHUTTERS" 0 (
      (11832.0611 839.6947) (10885.4962 839.6947)
    ))
    ; P1307 -- see feature_dimensions_mm.csv
    ("04_GLAZING_SHUTTERS" 0 (
      (10885.4962 824.4275) (10885.4962 839.6947)
    ))
    ; P1308 -- see feature_dimensions_mm.csv
    ("04_GLAZING_SHUTTERS" 0 (
      (10885.4962 824.4275) (11832.0611 824.4275)
    ))
    ; P1309 -- see feature_dimensions_mm.csv
    ("04_GLAZING_SHUTTERS" 0 (
      (10885.4962 702.2901) (10885.4962 824.4275)
    ))
    ; P1310 -- see feature_dimensions_mm.csv
    ("04_GLAZING_SHUTTERS" 0 (
      (11832.0611 702.2901) (10885.4962 702.2901)
    ))
    ; P1311 -- see feature_dimensions_mm.csv
    ("04_GLAZING_SHUTTERS" 0 (
      (11832.0611 702.2901) (11832.0611 671.7557) (10885.4962 671.7557) (10885.4962 702.2901)
    ))
    ; P1312 -- see feature_dimensions_mm.csv
    ("04_GLAZING_SHUTTERS" 0 (
      (11816.5649 1851.0076) (11816.7939 1844.2748) (11816.7939 1628.7023) (11816.7939 1608.9618) (11816.7939 1236.6412)
      (10900.7634 1236.6412) (10900.7634 1609.5878) (10900.7634 1629.7099) (10900.7634 1844.2748) (10901.0382 1851.9542)
    ))
    ; P1313 -- see feature_dimensions_mm.csv
    ("04_GLAZING_SHUTTERS" 0 (
      (10901.7405 1872.2137) (10901.7405 1872.4275) (10904.687 1900.4733) (10909.5573 1928.2748) (10916.3664 1955.7099)
      (10925.0687 1982.6718) (10935.6336 2009.0382) (10948.0 2034.7023) (10962.1221 2059.542) (10977.9542 2083.4656)
      (10995.4046 2106.3664) (11014.4275 2128.1527) (11034.916 2148.7023) (11056.7939 2167.9695) (11065.3893 2174.5954)
    ))
    ; P1314 -- see feature_dimensions_mm.csv
    ("04_GLAZING_SHUTTERS" 0 (
      (11081.8321 2187.0992) (11104.3206 2202.2443) (11129.771 2217.1298) (11156.1985 2230.4122) (11183.5115 2242.0305)
      (11211.5573 2251.9542) (11240.229 2260.1374) (11269.4198 2266.5344) (11298.9924 2271.1298) (11328.8244 2273.8931)
      (11358.7786 2274.8092) (11388.7328 2273.8931) (11418.5649 2271.1298) (11448.1374 2266.5344) (11477.3282 2260.1374)
      (11506.0 2251.9542) (11534.0611 2242.0305) (11561.3588 2230.4122) (11587.7863 2217.1298) (11613.2366 2202.2443)
      (11635.7252 2187.0992)
    ))
    ; P1315 -- see feature_dimensions_mm.csv
    ("04_GLAZING_SHUTTERS" 0 (
      (11652.1679 2174.5954) (11660.7634 2167.9695) (11682.6412 2148.7023) (11703.1298 2128.1527) (11722.1527 2106.3664)
      (11739.6031 2083.4656) (11755.4351 2059.542) (11769.5573 2034.7023) (11781.9237 2009.0382) (11792.4885 1982.6718)
      (11801.1908 1955.7099) (11808.0 1928.2748) (11812.8702 1900.4733) (11815.8168 1872.4275) (11815.8473 1871.5725)
    ))
    ; P1316 -- see feature_dimensions_mm.csv
    ("04_GLAZING_SHUTTERS" 0 (
      (11832.0611 1099.2366) (11832.0611 977.0992)
    ))
    ; P1317 -- see feature_dimensions_mm.csv
    ("04_GLAZING_SHUTTERS" 0 (
      (11832.0611 977.0992) (11832.0611 961.8321)
    ))
    ; P1318 -- see feature_dimensions_mm.csv
    ("04_GLAZING_SHUTTERS" 0 (
      (11832.0611 961.8321) (11832.0611 839.6947)
    ))
    ; P1319 -- see feature_dimensions_mm.csv
    ("04_GLAZING_SHUTTERS" 0 (
      (11832.0611 839.6947) (11832.0611 824.4275)
    ))
    ; P1320 -- see feature_dimensions_mm.csv
    ("04_GLAZING_SHUTTERS" 0 (
      (11832.0611 824.4275) (11832.0611 702.2901)
    ))
    ; P1321 -- see feature_dimensions_mm.csv
    ("04_GLAZING_SHUTTERS" 0 (
      (13175.5725 1099.2366) (12229.0076 1099.2366)
    ))
    ; P1322 -- see feature_dimensions_mm.csv
    ("04_GLAZING_SHUTTERS" 0 (
      (12229.0076 977.0992) (12229.0076 1099.2366)
    ))
    ; P1323 -- see feature_dimensions_mm.csv
    ("04_GLAZING_SHUTTERS" 0 (
      (12229.0076 1099.2366) (12229.0076 1221.374) (13175.5725 1221.374) (13175.5725 1099.2366)
    ))
    ; P1324 -- see feature_dimensions_mm.csv
    ("04_GLAZING_SHUTTERS" 0 (
      (13175.5725 977.0992) (12229.0076 977.0992)
    ))
    ; P1325 -- see feature_dimensions_mm.csv
    ("04_GLAZING_SHUTTERS" 0 (
      (12229.0076 961.8321) (12229.0076 977.0992)
    ))
    ; P1326 -- see feature_dimensions_mm.csv
    ("04_GLAZING_SHUTTERS" 0 (
      (12229.0076 961.8321) (13175.5725 961.8321)
    ))
    ; P1327 -- see feature_dimensions_mm.csv
    ("04_GLAZING_SHUTTERS" 0 (
      (12229.0076 839.6947) (12229.0076 961.8321)
    ))
    ; P1328 -- see feature_dimensions_mm.csv
    ("04_GLAZING_SHUTTERS" 0 (
      (13175.5725 839.6947) (12229.0076 839.6947)
    ))
    ; P1329 -- see feature_dimensions_mm.csv
    ("04_GLAZING_SHUTTERS" 0 (
      (12229.0076 824.4275) (12229.0076 839.6947)
    ))
    ; P1330 -- see feature_dimensions_mm.csv
    ("04_GLAZING_SHUTTERS" 0 (
      (12229.0076 824.4275) (13175.5725 824.4275)
    ))
    ; P1331 -- see feature_dimensions_mm.csv
    ("04_GLAZING_SHUTTERS" 0 (
      (12229.0076 702.2901) (12229.0076 824.4275)
    ))
    ; P1332 -- see feature_dimensions_mm.csv
    ("04_GLAZING_SHUTTERS" 0 (
      (13175.5725 702.2901) (12229.0076 702.2901)
    ))
    ; P1333 -- see feature_dimensions_mm.csv
    ("04_GLAZING_SHUTTERS" 0 (
      (13175.5725 702.2901) (13175.5725 671.7557) (12229.0076 671.7557) (12229.0076 702.2901)
    ))
    ; P1334 -- see feature_dimensions_mm.csv
    ("04_GLAZING_SHUTTERS" 0 (
      (12244.5496 1851.9542) (12244.2748 1844.2748) (12244.2748 1629.7099) (12244.2748 1609.5878) (12244.2748 1236.6412)
      (13160.3053 1236.6412) (13160.3053 1608.9618)
    ))
    ; P1335 -- see feature_dimensions_mm.csv
    ("04_GLAZING_SHUTTERS" 0 (
      (12408.9008 2174.5954) (12400.3053 2167.9695) (12378.4275 2148.7023) (12357.9389 2128.1527) (12338.916 2106.3664)
      (12321.4656 2083.4656) (12305.6336 2059.542) (12291.5115 2034.7023) (12279.145 2009.0382) (12268.5802 1982.6718)
      (12259.8779 1955.7099) (12253.0687 1928.2748) (12248.1985 1900.4733) (12245.2519 1872.4275) (12245.2519 1872.2137)
    ))
    ; P1336 -- see feature_dimensions_mm.csv
    ("04_GLAZING_SHUTTERS" 0 (
      (12979.2366 2187.0992) (12956.7481 2202.2443) (12931.2977 2217.1298) (12904.8702 2230.4122) (12877.5725 2242.0305)
      (12849.5115 2251.9542) (12820.8397 2260.1374) (12791.6489 2266.5344) (12762.0763 2271.1298) (12732.2443 2273.8931)
      (12702.2901 2274.8092) (12672.3359 2273.8931) (12642.5038 2271.1298) (12612.9313 2266.5344) (12583.7405 2260.1374)
      (12555.0687 2251.9542) (12527.0229 2242.0305) (12499.7099 2230.4122) (12473.2824 2217.1298) (12447.8321 2202.2443)
      (12425.3435 2187.0992)
    ))
    ; P1337 -- see feature_dimensions_mm.csv
    ("04_GLAZING_SHUTTERS" 0 (
      (12748.0916 2839.6947) (12732.8244 2839.6947) (12732.8244 2916.0305) (12732.8244 3007.6336) (12732.8244 3068.7023)
      (12793.8931 3068.7023) (12793.8931 3007.6336) (12793.8931 2916.0305) (12793.8931 2839.6947) (12778.626 2839.6947)
    ))
    ; P1338 -- see feature_dimensions_mm.csv
    ("04_GLAZING_SHUTTERS" 0 (
      (13159.3588 1871.5725) (13159.3282 1872.4275) (13156.3817 1900.4733) (13151.5115 1928.2748) (13144.7023 1955.7099)
      (13136.0 1982.6718) (13125.4351 2009.0382) (13113.0687 2034.7023) (13098.9466 2059.542) (13083.1145 2083.4656)
      (13065.6641 2106.3664) (13046.6412 2128.1527) (13026.1527 2148.7023) (13004.2748 2167.9695) (12995.6794 2174.5954)
    ))
    ; P1339 -- see feature_dimensions_mm.csv
    ("04_GLAZING_SHUTTERS" 0 (
      (13038.1679 2839.6947) (13022.9008 2839.6947) (13022.9008 2916.0305) (13022.9008 3007.6336) (13022.9008 3068.7023)
      (13083.9695 3068.7023) (13083.9695 3007.6336) (13083.9695 2916.0305) (13083.9695 2839.6947) (13068.7023 2839.6947)
    ))
    ; P1340 -- see feature_dimensions_mm.csv
    ("04_GLAZING_SHUTTERS" 0 (
      (13160.3053 1628.7023) (13160.3053 1844.2748) (13160.0763 1851.0076)
    ))
    ; P1341 -- see feature_dimensions_mm.csv
    ("04_GLAZING_SHUTTERS" 0 (
      (13175.5725 1099.2366) (13175.5725 977.0992)
    ))
    ; P1342 -- see feature_dimensions_mm.csv
    ("04_GLAZING_SHUTTERS" 0 (
      (13175.5725 977.0992) (13175.5725 961.8321)
    ))
    ; P1343 -- see feature_dimensions_mm.csv
    ("04_GLAZING_SHUTTERS" 0 (
      (13175.5725 961.8321) (13175.5725 839.6947)
    ))
    ; P1344 -- see feature_dimensions_mm.csv
    ("04_GLAZING_SHUTTERS" 0 (
      (13175.5725 839.6947) (13175.5725 824.4275)
    ))
    ; P1345 -- see feature_dimensions_mm.csv
    ("04_GLAZING_SHUTTERS" 0 (
      (13175.5725 824.4275) (13175.5725 702.2901)
    ))
    ; P1346 -- see feature_dimensions_mm.csv
    ("04_GLAZING_SHUTTERS" 1 (
      (259.542 7450.3817) (854.9618 7450.3817) (854.9618 5893.1298) (259.542 5893.1298)
    ))
    ; P1347 -- see feature_dimensions_mm.csv
    ("04_GLAZING_SHUTTERS" 1 (
      (259.542 5770.9924) (854.9618 5770.9924) (854.9618 4213.7405) (259.542 4213.7405)
    ))
    ; P1348 -- see feature_dimensions_mm.csv
    ("04_GLAZING_SHUTTERS" 1 (
      (1236.6412 7435.1145) (1358.7786 7435.1145) (1358.7786 7374.0458) (1358.7786 7282.4427) (1358.7786 7190.8397)
      (1358.7786 7145.0382) (1236.6412 7145.0382) (1236.6412 7190.8397) (1236.6412 7282.4427) (1236.6412 7374.0458)
    ))
    ; P1349 -- see feature_dimensions_mm.csv
    ("04_GLAZING_SHUTTERS" 1 (
      (1725.1908 7435.1145) (1847.3282 7435.1145) (1847.3282 7374.0458) (1847.3282 7282.4427) (1847.3282 7190.8397)
      (1847.3282 7145.0382) (1725.1908 7145.0382) (1725.1908 7190.8397) (1725.1908 7282.4427) (1725.1908 7374.0458)
    ))
    ; P1350 -- see feature_dimensions_mm.csv
    ("04_GLAZING_SHUTTERS" 1 (
      (1969.4656 3068.7023) (2030.5344 3068.7023) (2030.5344 3007.6336) (2030.5344 2916.0305) (2030.5344 2839.6947)
      (2015.2672 2839.6947) (1984.7328 2839.6947) (1969.4656 2839.6947) (1969.4656 2916.0305) (1969.4656 3007.6336)
    ))
    ; P1351 -- see feature_dimensions_mm.csv
    ("04_GLAZING_SHUTTERS" 1 (
      (2198.4733 7435.1145) (2320.6107 7435.1145) (2320.6107 7374.0458) (2320.6107 7282.4427) (2320.6107 7190.8397)
      (2320.6107 7145.0382) (2198.4733 7145.0382) (2198.4733 7190.8397) (2198.4733 7282.4427) (2198.4733 7374.0458)
    ))
    ; P1352 -- see feature_dimensions_mm.csv
    ("04_GLAZING_SHUTTERS" 1 (
      (2259.542 3068.7023) (2320.6107 3068.7023) (2320.6107 3007.6336) (2320.6107 2916.0305) (2320.6107 2839.6947)
      (2305.3435 2839.6947) (2274.8092 2839.6947) (2259.542 2839.6947) (2259.542 2916.0305) (2259.542 3007.6336)
    ))
    ; P1353 -- see feature_dimensions_mm.csv
    ("04_GLAZING_SHUTTERS" 1 (
      (2549.6183 3068.7023) (2610.687 3068.7023) (2610.687 3007.6336) (2610.687 2916.0305) (2610.687 2839.6947)
      (2595.4198 2839.6947) (2564.8855 2839.6947) (2549.6183 2839.6947) (2549.6183 2916.0305) (2549.6183 3007.6336)
    ))
    ; P1354 -- see feature_dimensions_mm.csv
    ("04_GLAZING_SHUTTERS" 1 (
      (2687.0229 7435.1145) (2809.1603 7435.1145) (2809.1603 7374.0458) (2809.1603 7282.4427) (2809.1603 7190.8397)
      (2809.1603 7145.0382) (2687.0229 7145.0382) (2687.0229 7190.8397) (2687.0229 7282.4427) (2687.0229 7374.0458)
    ))
    ; P1355 -- see feature_dimensions_mm.csv
    ("04_GLAZING_SHUTTERS" 1 (
      (3160.3053 7435.1145) (3282.4427 7435.1145) (3282.4427 7374.0458) (3282.4427 7282.4427) (3282.4427 7190.8397)
      (3282.4427 7145.0382) (3160.3053 7145.0382) (3160.3053 7190.8397) (3160.3053 7282.4427) (3160.3053 7374.0458)
    ))
    ; P1356 -- see feature_dimensions_mm.csv
    ("04_GLAZING_SHUTTERS" 1 (
      (3374.0458 3068.7023) (3435.1145 3068.7023) (3435.1145 3007.6336) (3435.1145 2916.0305) (3435.1145 2839.6947)
      (3419.8473 2839.6947) (3389.313 2839.6947) (3374.0458 2839.6947) (3374.0458 2916.0305) (3374.0458 3007.6336)
    ))
    ; P1357 -- see feature_dimensions_mm.csv
    ("04_GLAZING_SHUTTERS" 1 (
      (3648.855 7435.1145) (3770.9924 7435.1145) (3770.9924 7374.0458) (3770.9924 7282.4427) (3770.9924 7190.8397)
      (3770.9924 7145.0382) (3648.855 7145.0382) (3648.855 7190.8397) (3648.855 7282.4427) (3648.855 7374.0458)
    ))
    ; P1358 -- see feature_dimensions_mm.csv
    ("04_GLAZING_SHUTTERS" 1 (
      (3664.1221 3068.7023) (3725.1908 3068.7023) (3725.1908 3007.6336) (3725.1908 2916.0305) (3725.1908 2839.6947)
      (3709.9237 2839.6947) (3679.3893 2839.6947) (3664.1221 2839.6947) (3664.1221 2916.0305) (3664.1221 3007.6336)
    ))
    ; P1359 -- see feature_dimensions_mm.csv
    ("04_GLAZING_SHUTTERS" 1 (
      (3954.1985 3068.7023) (4015.2672 3068.7023) (4015.2672 3007.6336) (4015.2672 2916.0305) (4015.2672 2839.6947)
      (4000.0 2839.6947) (3969.4656 2839.6947) (3954.1985 2839.6947) (3954.1985 2916.0305) (3954.1985 3007.6336)
    ))
    ; P1360 -- see feature_dimensions_mm.csv
    ("04_GLAZING_SHUTTERS" 1 (
      (4122.1374 7435.1145) (4244.2748 7435.1145) (4244.2748 7374.0458) (4244.2748 7282.4427) (4244.2748 7190.8397)
      (4244.2748 7145.0382) (4122.1374 7145.0382) (4122.1374 7190.8397) (4122.1374 7282.4427) (4122.1374 7374.0458)
    ))
    ; P1361 -- see feature_dimensions_mm.csv
    ("04_GLAZING_SHUTTERS" 1 (
      (4610.687 7435.1145) (4732.8244 7435.1145) (4732.8244 7374.0458) (4732.8244 7282.4427) (4732.8244 7190.8397)
      (4732.8244 7145.0382) (4610.687 7145.0382) (4610.687 7190.8397) (4610.687 7282.4427) (4610.687 7374.0458)
    ))
    ; P1362 -- see feature_dimensions_mm.csv
    ("04_GLAZING_SHUTTERS" 1 (
      (5450.3817 4503.8168) (5908.3969 4503.8168) (5908.3969 4432.0611) (5450.3817 4432.0611)
    ))
    ; P1363 -- see feature_dimensions_mm.csv
    ("04_GLAZING_SHUTTERS" 1 (
      (5450.3817 4400.0) (5908.3969 4400.0) (5908.3969 4328.2443) (5450.3817 4328.2443)
    ))
    ; P1364 -- see feature_dimensions_mm.csv
    ("04_GLAZING_SHUTTERS" 1 (
      (5450.3817 4296.1832) (5908.3969 4296.1832) (5908.3969 4224.4275) (5450.3817 4224.4275)
    ))
    ; P1365 -- see feature_dimensions_mm.csv
    ("04_GLAZING_SHUTTERS" 1 (
      (5450.3817 4192.3664) (5908.3969 4192.3664) (5908.3969 4120.6107) (5450.3817 4120.6107)
    ))
    ; P1366 -- see feature_dimensions_mm.csv
    ("04_GLAZING_SHUTTERS" 1 (
      (5450.3817 4088.5496) (5908.3969 4088.5496) (5908.3969 4016.7939) (5450.3817 4016.7939)
    ))
    ; P1367 -- see feature_dimensions_mm.csv
    ("04_GLAZING_SHUTTERS" 1 (
      (5450.3817 3984.7328) (5908.3969 3984.7328) (5908.3969 3912.9771) (5450.3817 3912.9771)
    ))
    ; P1368 -- see feature_dimensions_mm.csv
    ("04_GLAZING_SHUTTERS" 1 (
      (5450.3817 3880.916) (5908.3969 3880.916) (5908.3969 3809.1603) (5450.3817 3809.1603)
    ))
    ; P1369 -- see feature_dimensions_mm.csv
    ("04_GLAZING_SHUTTERS" 1 (
      (5450.3817 3777.0992) (5908.3969 3777.0992) (5908.3969 3705.3435) (5450.3817 3705.3435)
    ))
    ; P1370 -- see feature_dimensions_mm.csv
    ("04_GLAZING_SHUTTERS" 1 (
      (5450.3817 3673.2824) (5908.3969 3673.2824) (5908.3969 3601.5267) (5450.3817 3601.5267)
    ))
    ; P1371 -- see feature_dimensions_mm.csv
    ("04_GLAZING_SHUTTERS" 1 (
      (5450.3817 3569.4656) (5908.3969 3569.4656) (5908.3969 3497.7099) (5450.3817 3497.7099)
    ))
    ; P1372 -- see feature_dimensions_mm.csv
    ("04_GLAZING_SHUTTERS" 1 (
      (5450.3817 3465.6489) (5908.3969 3465.6489) (5908.3969 3393.8931) (5450.3817 3393.8931)
    ))
    ; P1373 -- see feature_dimensions_mm.csv
    ("04_GLAZING_SHUTTERS" 1 (
      (5450.3817 3361.8321) (5908.3969 3361.8321) (5908.3969 3290.0763) (5450.3817 3290.0763)
    ))
    ; P1374 -- see feature_dimensions_mm.csv
    ("04_GLAZING_SHUTTERS" 1 (
      (5450.3817 3258.0153) (5908.3969 3258.0153) (5908.3969 3186.2595) (5450.3817 3186.2595)
    ))
    ; P1375 -- see feature_dimensions_mm.csv
    ("04_GLAZING_SHUTTERS" 1 (
      (5450.3817 3154.1985) (5908.3969 3154.1985) (5908.3969 3082.4427) (5450.3817 3082.4427)
    ))
    ; P1376 -- see feature_dimensions_mm.csv
    ("04_GLAZING_SHUTTERS" 1 (
      (5450.3817 3050.3817) (5908.3969 3050.3817) (5908.3969 2978.626) (5450.3817 2978.626)
    ))
    ; P1377 -- see feature_dimensions_mm.csv
    ("04_GLAZING_SHUTTERS" 1 (
      (5450.3817 2946.5649) (5908.3969 2946.5649) (5908.3969 2874.8092) (5450.3817 2874.8092)
    ))
    ; P1378 -- see feature_dimensions_mm.csv
    ("04_GLAZING_SHUTTERS" 1 (
      (5450.3817 2842.7481) (5908.3969 2842.7481) (5908.3969 2770.9924) (5450.3817 2770.9924)
    ))
    ; P1379 -- see feature_dimensions_mm.csv
    ("04_GLAZING_SHUTTERS" 1 (
      (5450.3817 2738.9313) (5908.3969 2738.9313) (5908.3969 2667.1756) (5450.3817 2667.1756)
    ))
    ; P1380 -- see feature_dimensions_mm.csv
    ("04_GLAZING_SHUTTERS" 1 (
      (5450.3817 2635.1145) (5908.3969 2635.1145) (5908.3969 2563.3588) (5450.3817 2563.3588)
    ))
    ; P1381 -- see feature_dimensions_mm.csv
    ("04_GLAZING_SHUTTERS" 1 (
      (5450.3817 2531.2977) (5908.3969 2531.2977) (5908.3969 2459.542) (5450.3817 2459.542)
    ))
    ; P1382 -- see feature_dimensions_mm.csv
    ("04_GLAZING_SHUTTERS" 1 (
      (5450.3817 2335.8779) (5908.3969 2335.8779) (5908.3969 1251.9084) (5450.3817 1251.9084)
    ))
    ; P1383 -- see feature_dimensions_mm.csv
    ("04_GLAZING_SHUTTERS" 1 (
      (5526.7176 5328.2443) (5633.5878 5129.771) (5526.7176 4580.1527) (5832.0611 4580.1527) (5725.1908 5129.771)
      (5832.0611 5328.2443) (5679.3893 5526.7176)
    ))
    ; P1384 -- see feature_dimensions_mm.csv
    ("04_GLAZING_SHUTTERS" 1 (
      (5557.2519 2290.0763) (5557.2519 1877.8626) (5633.5878 1709.9237) (5557.2519 1480.916) (5557.2519 1282.4427)
      (5801.5267 1282.4427) (5801.5267 1480.916) (5725.1908 1709.9237) (5801.5267 1877.8626) (5801.5267 2290.0763)
    ))
    ; P1385 -- see feature_dimensions_mm.csv
    ("04_GLAZING_SHUTTERS" 1 (
      (6427.4809 4503.8168) (7312.9771 4503.8168) (7312.9771 4432.0611) (6427.4809 4432.0611)
    ))
    ; P1386 -- see feature_dimensions_mm.csv
    ("04_GLAZING_SHUTTERS" 1 (
      (6427.4809 4400.0) (7312.9771 4400.0) (7312.9771 4328.2443) (6427.4809 4328.2443)
    ))
    ; P1387 -- see feature_dimensions_mm.csv
    ("04_GLAZING_SHUTTERS" 1 (
      (6427.4809 4296.1832) (7312.9771 4296.1832) (7312.9771 4224.4275) (6427.4809 4224.4275)
    ))
    ; P1388 -- see feature_dimensions_mm.csv
    ("04_GLAZING_SHUTTERS" 1 (
      (6427.4809 4192.3664) (7312.9771 4192.3664) (7312.9771 4120.6107) (6427.4809 4120.6107)
    ))
    ; P1389 -- see feature_dimensions_mm.csv
    ("04_GLAZING_SHUTTERS" 1 (
      (6427.4809 4088.5496) (7312.9771 4088.5496) (7312.9771 4016.7939) (6427.4809 4016.7939)
    ))
    ; P1390 -- see feature_dimensions_mm.csv
    ("04_GLAZING_SHUTTERS" 1 (
      (6427.4809 3984.7328) (7312.9771 3984.7328) (7312.9771 3912.9771) (6427.4809 3912.9771)
    ))
    ; P1391 -- see feature_dimensions_mm.csv
    ("04_GLAZING_SHUTTERS" 1 (
      (6427.4809 3880.916) (7312.9771 3880.916) (7312.9771 3809.1603) (6427.4809 3809.1603)
    ))
    ; P1392 -- see feature_dimensions_mm.csv
    ("04_GLAZING_SHUTTERS" 1 (
      (6427.4809 3777.0992) (7312.9771 3777.0992) (7312.9771 3705.3435) (6427.4809 3705.3435)
    ))
    ; P1393 -- see feature_dimensions_mm.csv
    ("04_GLAZING_SHUTTERS" 1 (
      (6427.4809 3673.2824) (7312.9771 3673.2824) (7312.9771 3601.5267) (6427.4809 3601.5267)
    ))
    ; P1394 -- see feature_dimensions_mm.csv
    ("04_GLAZING_SHUTTERS" 1 (
      (6427.4809 3569.4656) (7312.9771 3569.4656) (7312.9771 3497.7099) (6427.4809 3497.7099)
    ))
    ; P1395 -- see feature_dimensions_mm.csv
    ("04_GLAZING_SHUTTERS" 1 (
      (6427.4809 3465.6489) (7312.9771 3465.6489) (7312.9771 3393.8931) (6427.4809 3393.8931)
    ))
    ; P1396 -- see feature_dimensions_mm.csv
    ("04_GLAZING_SHUTTERS" 1 (
      (6427.4809 3361.8321) (7312.9771 3361.8321) (7312.9771 3290.0763) (6427.4809 3290.0763)
    ))
    ; P1397 -- see feature_dimensions_mm.csv
    ("04_GLAZING_SHUTTERS" 1 (
      (6427.4809 3258.0153) (7312.9771 3258.0153) (7312.9771 3186.2595) (6427.4809 3186.2595)
    ))
    ; P1398 -- see feature_dimensions_mm.csv
    ("04_GLAZING_SHUTTERS" 1 (
      (6427.4809 3154.1985) (7312.9771 3154.1985) (7312.9771 3082.4427) (6427.4809 3082.4427)
    ))
    ; P1399 -- see feature_dimensions_mm.csv
    ("04_GLAZING_SHUTTERS" 1 (
      (6427.4809 3050.3817) (7312.9771 3050.3817) (7312.9771 2978.626) (6427.4809 2978.626)
    ))
    ; P1400 -- see feature_dimensions_mm.csv
    ("04_GLAZING_SHUTTERS" 1 (
      (6427.4809 2946.5649) (7312.9771 2946.5649) (7312.9771 2874.8092) (6427.4809 2874.8092)
    ))
    ; P1401 -- see feature_dimensions_mm.csv
    ("04_GLAZING_SHUTTERS" 1 (
      (6427.4809 2842.7481) (7312.9771 2842.7481) (7312.9771 2770.9924) (6427.4809 2770.9924)
    ))
    ; P1402 -- see feature_dimensions_mm.csv
    ("04_GLAZING_SHUTTERS" 1 (
      (6427.4809 2738.9313) (7312.9771 2738.9313) (7312.9771 2667.1756) (6427.4809 2667.1756)
    ))
    ; P1403 -- see feature_dimensions_mm.csv
    ("04_GLAZING_SHUTTERS" 1 (
      (6427.4809 2635.1145) (7312.9771 2635.1145) (7312.9771 2563.3588) (6427.4809 2563.3588)
    ))
    ; P1404 -- see feature_dimensions_mm.csv
    ("04_GLAZING_SHUTTERS" 1 (
      (6427.4809 2531.2977) (7312.9771 2531.2977) (7312.9771 2459.542) (6427.4809 2459.542)
    ))
    ; P1405 -- see feature_dimensions_mm.csv
    ("04_GLAZING_SHUTTERS" 1 (
      (6427.4809 2335.8779) (7312.9771 2335.8779) (7312.9771 1251.9084) (6427.4809 1251.9084)
    ))
    ; P1406 -- see feature_dimensions_mm.csv
    ("04_GLAZING_SHUTTERS" 1 (
      (6442.7481 5267.1756) (6442.7481 4549.6183) (6717.5573 4549.6183) (6824.4275 5007.6336)
    ))
    ; P1407 -- see feature_dimensions_mm.csv
    ("04_GLAZING_SHUTTERS" 1 (
      (6656.4885 5236.6412) (6870.229 5022.9008) (7083.9695 5236.6412) (6870.229 5511.4504)
    ))
    ; P1408 -- see feature_dimensions_mm.csv
    ("04_GLAZING_SHUTTERS" 1 (
      (6916.0305 5007.6336) (7022.9008 4549.6183) (7297.7099 4549.6183) (7297.7099 5267.1756)
    ))
    ; P1409 -- see feature_dimensions_mm.csv
    ("04_GLAZING_SHUTTERS" 1 (
      (7847.3282 4503.8168) (8290.0763 4503.8168) (8290.0763 4432.0611) (7847.3282 4432.0611)
    ))
    ; P1410 -- see feature_dimensions_mm.csv
    ("04_GLAZING_SHUTTERS" 1 (
      (7847.3282 4400.0) (8290.0763 4400.0) (8290.0763 4328.2443) (7847.3282 4328.2443)
    ))
    ; P1411 -- see feature_dimensions_mm.csv
    ("04_GLAZING_SHUTTERS" 1 (
      (7847.3282 4296.1832) (8290.0763 4296.1832) (8290.0763 4224.4275) (7847.3282 4224.4275)
    ))
    ; P1412 -- see feature_dimensions_mm.csv
    ("04_GLAZING_SHUTTERS" 1 (
      (7847.3282 4192.3664) (8290.0763 4192.3664) (8290.0763 4120.6107) (7847.3282 4120.6107)
    ))
    ; P1413 -- see feature_dimensions_mm.csv
    ("04_GLAZING_SHUTTERS" 1 (
      (7847.3282 4088.5496) (8290.0763 4088.5496) (8290.0763 4016.7939) (7847.3282 4016.7939)
    ))
    ; P1414 -- see feature_dimensions_mm.csv
    ("04_GLAZING_SHUTTERS" 1 (
      (7847.3282 3984.7328) (8290.0763 3984.7328) (8290.0763 3912.9771) (7847.3282 3912.9771)
    ))
    ; P1415 -- see feature_dimensions_mm.csv
    ("04_GLAZING_SHUTTERS" 1 (
      (7847.3282 3880.916) (8290.0763 3880.916) (8290.0763 3809.1603) (7847.3282 3809.1603)
    ))
    ; P1416 -- see feature_dimensions_mm.csv
    ("04_GLAZING_SHUTTERS" 1 (
      (7847.3282 3777.0992) (8290.0763 3777.0992) (8290.0763 3705.3435) (7847.3282 3705.3435)
    ))
    ; P1417 -- see feature_dimensions_mm.csv
    ("04_GLAZING_SHUTTERS" 1 (
      (7847.3282 3673.2824) (8290.0763 3673.2824) (8290.0763 3601.5267) (7847.3282 3601.5267)
    ))
    ; P1418 -- see feature_dimensions_mm.csv
    ("04_GLAZING_SHUTTERS" 1 (
      (7847.3282 3569.4656) (8290.0763 3569.4656) (8290.0763 3497.7099) (7847.3282 3497.7099)
    ))
    ; P1419 -- see feature_dimensions_mm.csv
    ("04_GLAZING_SHUTTERS" 1 (
      (7847.3282 3465.6489) (8290.0763 3465.6489) (8290.0763 3393.8931) (7847.3282 3393.8931)
    ))
    ; P1420 -- see feature_dimensions_mm.csv
    ("04_GLAZING_SHUTTERS" 1 (
      (7847.3282 3361.8321) (8290.0763 3361.8321) (8290.0763 3290.0763) (7847.3282 3290.0763)
    ))
    ; P1421 -- see feature_dimensions_mm.csv
    ("04_GLAZING_SHUTTERS" 1 (
      (7847.3282 3258.0153) (8290.0763 3258.0153) (8290.0763 3186.2595) (7847.3282 3186.2595)
    ))
    ; P1422 -- see feature_dimensions_mm.csv
    ("04_GLAZING_SHUTTERS" 1 (
      (7847.3282 3154.1985) (8290.0763 3154.1985) (8290.0763 3082.4427) (7847.3282 3082.4427)
    ))
    ; P1423 -- see feature_dimensions_mm.csv
    ("04_GLAZING_SHUTTERS" 1 (
      (7847.3282 3050.3817) (8290.0763 3050.3817) (8290.0763 2978.626) (7847.3282 2978.626)
    ))
    ; P1424 -- see feature_dimensions_mm.csv
    ("04_GLAZING_SHUTTERS" 1 (
      (7847.3282 2946.5649) (8290.0763 2946.5649) (8290.0763 2874.8092) (7847.3282 2874.8092)
    ))
    ; P1425 -- see feature_dimensions_mm.csv
    ("04_GLAZING_SHUTTERS" 1 (
      (7847.3282 2842.7481) (8290.0763 2842.7481) (8290.0763 2770.9924) (7847.3282 2770.9924)
    ))
    ; P1426 -- see feature_dimensions_mm.csv
    ("04_GLAZING_SHUTTERS" 1 (
      (7847.3282 2738.9313) (8290.0763 2738.9313) (8290.0763 2667.1756) (7847.3282 2667.1756)
    ))
    ; P1427 -- see feature_dimensions_mm.csv
    ("04_GLAZING_SHUTTERS" 1 (
      (7847.3282 2635.1145) (8290.0763 2635.1145) (8290.0763 2563.3588) (7847.3282 2563.3588)
    ))
    ; P1428 -- see feature_dimensions_mm.csv
    ("04_GLAZING_SHUTTERS" 1 (
      (7847.3282 2531.2977) (8290.0763 2531.2977) (8290.0763 2459.542) (7847.3282 2459.542)
    ))
    ; P1429 -- see feature_dimensions_mm.csv
    ("04_GLAZING_SHUTTERS" 1 (
      (7847.3282 2335.8779) (8290.0763 2335.8779) (8290.0763 1251.9084) (7847.3282 1251.9084)
    ))
    ; P1430 -- see feature_dimensions_mm.csv
    ("04_GLAZING_SHUTTERS" 1 (
      (7916.0305 5328.2443) (8022.9008 5129.771) (7916.0305 4580.1527) (8221.374 4580.1527) (8114.5038 5129.771)
      (8221.374 5328.2443) (8068.7023 5526.7176)
    ))
    ; P1431 -- see feature_dimensions_mm.csv
    ("04_GLAZING_SHUTTERS" 1 (
      (7946.5649 2290.0763) (7946.5649 1877.8626) (8022.9008 1709.9237) (7946.5649 1480.916) (7946.5649 1282.4427)
      (8190.8397 1282.4427) (8190.8397 1480.916) (8114.5038 1709.9237) (8190.8397 1877.8626) (8190.8397 2290.0763)
    ))
    ; P1432 -- see feature_dimensions_mm.csv
    ("04_GLAZING_SHUTTERS" 1 (
      (9022.9008 7450.3817) (9022.9008 7389.313) (9022.9008 7297.7099) (9022.9008 7206.1069) (9022.9008 7145.0382)
      (9145.0382 7145.0382) (9145.0382 7206.1069) (9145.0382 7297.7099) (9145.0382 7389.313) (9145.0382 7450.3817)
    ))
    ; P1433 -- see feature_dimensions_mm.csv
    ("04_GLAZING_SHUTTERS" 1 (
      (9435.1145 7450.3817) (9435.1145 7389.313) (9435.1145 7297.7099) (9435.1145 7206.1069) (9435.1145 7145.0382)
      (9557.2519 7145.0382) (9557.2519 7206.1069) (9557.2519 7297.7099) (9557.2519 7389.313) (9557.2519 7450.3817)
    ))
    ; P1434 -- see feature_dimensions_mm.csv
    ("04_GLAZING_SHUTTERS" 1 (
      (9847.3282 7450.3817) (9847.3282 7389.313) (9847.3282 7297.7099) (9847.3282 7206.1069) (9847.3282 7145.0382)
      (9969.4656 7145.0382) (9969.4656 7206.1069) (9969.4656 7297.7099) (9969.4656 7389.313) (9969.4656 7450.3817)
    ))
    ; P1435 -- see feature_dimensions_mm.csv
    ("04_GLAZING_SHUTTERS" 1 (
      (10549.6183 7435.1145) (10671.7557 7435.1145) (10671.7557 7374.0458) (10671.7557 7282.4427) (10671.7557 7190.8397)
      (10671.7557 7145.0382) (10549.6183 7145.0382) (10549.6183 7190.8397) (10549.6183 7282.4427) (10549.6183 7374.0458)
    ))
    ; P1436 -- see feature_dimensions_mm.csv
    ("04_GLAZING_SHUTTERS" 1 (
      (11038.1679 7435.1145) (11160.3053 7435.1145) (11160.3053 7374.0458) (11160.3053 7282.4427) (11160.3053 7190.8397)
      (11160.3053 7145.0382) (11038.1679 7145.0382) (11038.1679 7190.8397) (11038.1679 7282.4427) (11038.1679 7374.0458)
    ))
    ; P1437 -- see feature_dimensions_mm.csv
    ("04_GLAZING_SHUTTERS" 1 (
      (11068.7023 3068.7023) (11129.771 3068.7023) (11129.771 3007.6336) (11129.771 2916.0305) (11129.771 2839.6947)
      (11114.5038 2839.6947) (11083.9695 2839.6947) (11068.7023 2839.6947) (11068.7023 2916.0305) (11068.7023 3007.6336)
    ))
    ; P1438 -- see feature_dimensions_mm.csv
    ("04_GLAZING_SHUTTERS" 1 (
      (11343.5115 3068.7023) (11404.5802 3068.7023) (11404.5802 3007.6336) (11404.5802 2916.0305) (11404.5802 2839.6947)
      (11389.313 2839.6947) (11358.7786 2839.6947) (11343.5115 2839.6947) (11343.5115 2916.0305) (11343.5115 3007.6336)
    ))
    ; P1439 -- see feature_dimensions_mm.csv
    ("04_GLAZING_SHUTTERS" 1 (
      (11526.7176 7435.1145) (11648.855 7435.1145) (11648.855 7374.0458) (11648.855 7282.4427) (11648.855 7190.8397)
      (11648.855 7145.0382) (11526.7176 7145.0382) (11526.7176 7190.8397) (11526.7176 7282.4427) (11526.7176 7374.0458)
    ))
    ; P1440 -- see feature_dimensions_mm.csv
    ("04_GLAZING_SHUTTERS" 1 (
      (11633.5878 3068.7023) (11694.6565 3068.7023) (11694.6565 3007.6336) (11694.6565 2916.0305) (11694.6565 2839.6947)
      (11679.3893 2839.6947) (11648.855 2839.6947) (11633.5878 2839.6947) (11633.5878 2916.0305) (11633.5878 3007.6336)
    ))
    ; P1441 -- see feature_dimensions_mm.csv
    ("04_GLAZING_SHUTTERS" 1 (
      (12015.2672 7435.1145) (12137.4046 7435.1145) (12137.4046 7374.0458) (12137.4046 7282.4427) (12137.4046 7190.8397)
      (12137.4046 7145.0382) (12015.2672 7145.0382) (12015.2672 7190.8397) (12015.2672 7282.4427) (12015.2672 7374.0458)
    ))
    ; P1442 -- see feature_dimensions_mm.csv
    ("04_GLAZING_SHUTTERS" 1 (
      (12442.7481 3068.7023) (12503.8168 3068.7023) (12503.8168 3007.6336) (12503.8168 2916.0305) (12503.8168 2839.6947)
      (12488.5496 2839.6947) (12458.0153 2839.6947) (12442.7481 2839.6947) (12442.7481 2916.0305) (12442.7481 3007.6336)
    ))
    ; P1443 -- see feature_dimensions_mm.csv
    ("04_GLAZING_SHUTTERS" 1 (
      (12503.8168 7435.1145) (12625.9542 7435.1145) (12625.9542 7374.0458) (12625.9542 7282.4427) (12625.9542 7190.8397)
      (12625.9542 7145.0382) (12503.8168 7145.0382) (12503.8168 7190.8397) (12503.8168 7282.4427) (12503.8168 7374.0458)
    ))
    ; P1444 -- see feature_dimensions_mm.csv
    ("04_GLAZING_SHUTTERS" 1 (
      (12992.3664 7435.1145) (13114.5038 7435.1145) (13114.5038 7374.0458) (13114.5038 7282.4427) (13114.5038 7190.8397)
      (13114.5038 7145.0382) (12992.3664 7145.0382) (12992.3664 7190.8397) (12992.3664 7282.4427) (12992.3664 7374.0458)
    ))
    ; P1445 -- see feature_dimensions_mm.csv
    ("04_GLAZING_SHUTTERS" 1 (
      (13465.6489 7435.1145) (13587.7863 7435.1145) (13587.7863 7374.0458) (13587.7863 7282.4427) (13587.7863 7190.8397)
      (13587.7863 7145.0382) (13465.6489 7145.0382) (13465.6489 7190.8397) (13465.6489 7282.4427) (13465.6489 7374.0458)
    ))
    ; P1446 -- see feature_dimensions_mm.csv
    ("05_STONE_JOINTS" 0 (
      (183.2061 9358.7786) (296.1832 9358.7786)
    ))
    ; P1447 -- see feature_dimensions_mm.csv
    ("05_STONE_JOINTS" 0 (
      (183.2061 9358.7786) (183.2061 9145.0382) (296.1832 9145.0382)
    ))
    ; P1448 -- see feature_dimensions_mm.csv
    ("05_STONE_JOINTS" 0 (
      (606.8702 9572.5191) (183.2061 9572.5191) (183.2061 9557.2519) (183.2061 9358.7786)
    ))
    ; P1449 -- see feature_dimensions_mm.csv
    ("05_STONE_JOINTS" 0 (
      (183.2061 8931.2977) (578.626 8931.2977)
    ))
    ; P1450 -- see feature_dimensions_mm.csv
    ("05_STONE_JOINTS" 0 (
      (183.2061 8717.5573) (578.626 8717.5573)
    ))
    ; P1451 -- see feature_dimensions_mm.csv
    ("05_STONE_JOINTS" 0 (
      (183.2061 8503.8168) (296.1832 8503.8168)
    ))
    ; P1452 -- see feature_dimensions_mm.csv
    ("05_STONE_JOINTS" 0 (
      (183.2061 8290.0763) (296.1832 8290.0763)
    ))
    ; P1453 -- see feature_dimensions_mm.csv
    ("05_STONE_JOINTS" 0 (
      (183.2061 8076.3359) (296.1832 8076.3359)
    ))
    ; P1454 -- see feature_dimensions_mm.csv
    ("05_STONE_JOINTS" 0 (
      (183.2061 7862.5954) (296.1832 7862.5954)
    ))
    ; P1455 -- see feature_dimensions_mm.csv
    ("05_STONE_JOINTS" 0 (
      (183.2061 7648.855) (578.626 7648.855)
    ))
    ; P1456 -- see feature_dimensions_mm.csv
    ("05_STONE_JOINTS" 0 (
      (183.2061 7435.1145) (213.7405 7435.1145)
    ))
    ; P1457 -- see feature_dimensions_mm.csv
    ("05_STONE_JOINTS" 0 (
      (183.2061 7221.374) (213.7405 7221.374)
    ))
    ; P1458 -- see feature_dimensions_mm.csv
    ("05_STONE_JOINTS" 0 (
      (183.2061 6793.8931) (213.7405 6793.8931)
    ))
    ; P1459 -- see feature_dimensions_mm.csv
    ("05_STONE_JOINTS" 0 (
      (183.2061 6793.8931) (183.2061 6580.1527)
    ))
    ; P1460 -- see feature_dimensions_mm.csv
    ("05_STONE_JOINTS" 0 (
      (213.7405 6793.8931) (213.7405 7007.6336) (183.2061 7007.6336) (183.2061 6793.8931)
    ))
    ; P1461 -- see feature_dimensions_mm.csv
    ("05_STONE_JOINTS" 0 (
      (183.2061 6580.1527) (213.7405 6580.1527) (213.7405 6793.8931)
    ))
    ; P1462 -- see feature_dimensions_mm.csv
    ("05_STONE_JOINTS" 0 (
      (183.2061 6580.1527) (183.2061 6366.4122)
    ))
    ; P1463 -- see feature_dimensions_mm.csv
    ("05_STONE_JOINTS" 0 (
      (183.2061 6366.4122) (213.7405 6366.4122)
    ))
    ; P1464 -- see feature_dimensions_mm.csv
    ("05_STONE_JOINTS" 0 (
      (183.2061 6366.4122) (183.2061 6152.6718)
    ))
    ; P1465 -- see feature_dimensions_mm.csv
    ("05_STONE_JOINTS" 0 (
      (183.2061 6152.6718) (213.7405 6152.6718)
    ))
    ; P1466 -- see feature_dimensions_mm.csv
    ("05_STONE_JOINTS" 0 (
      (183.2061 6152.6718) (183.2061 5938.9313)
    ))
    ; P1467 -- see feature_dimensions_mm.csv
    ("05_STONE_JOINTS" 0 (
      (183.2061 5938.9313) (213.7405 5938.9313)
    ))
    ; P1468 -- see feature_dimensions_mm.csv
    ("05_STONE_JOINTS" 0 (
      (183.2061 5938.9313) (183.2061 5725.1908) (213.7405 5725.1908)
    ))
    ; P1469 -- see feature_dimensions_mm.csv
    ("05_STONE_JOINTS" 0 (
      (183.2061 5511.4504) (213.7405 5511.4504)
    ))
    ; P1470 -- see feature_dimensions_mm.csv
    ("05_STONE_JOINTS" 0 (
      (183.2061 5404.5802) (213.7405 5404.5802) (213.7405 5297.7099)
    ))
    ; P1471 -- see feature_dimensions_mm.csv
    ("05_STONE_JOINTS" 0 (
      (183.2061 5083.9695) (213.7405 5083.9695) (213.7405 5297.7099)
    ))
    ; P1472 -- see feature_dimensions_mm.csv
    ("05_STONE_JOINTS" 0 (
      (183.2061 5083.9695) (183.2061 4870.229)
    ))
    ; P1473 -- see feature_dimensions_mm.csv
    ("05_STONE_JOINTS" 0 (
      (183.2061 5083.9695) (183.2061 5297.7099) (213.7405 5297.7099)
    ))
    ; P1474 -- see feature_dimensions_mm.csv
    ("05_STONE_JOINTS" 0 (
      (183.2061 4870.229) (213.7405 4870.229)
    ))
    ; P1475 -- see feature_dimensions_mm.csv
    ("05_STONE_JOINTS" 0 (
      (183.2061 4870.229) (183.2061 4656.4885)
    ))
    ; P1476 -- see feature_dimensions_mm.csv
    ("05_STONE_JOINTS" 0 (
      (183.2061 4656.4885) (213.7405 4656.4885)
    ))
    ; P1477 -- see feature_dimensions_mm.csv
    ("05_STONE_JOINTS" 0 (
      (183.2061 4656.4885) (183.2061 4442.7481)
    ))
    ; P1478 -- see feature_dimensions_mm.csv
    ("05_STONE_JOINTS" 0 (
      (183.2061 4442.7481) (213.7405 4442.7481)
    ))
    ; P1479 -- see feature_dimensions_mm.csv
    ("05_STONE_JOINTS" 0 (
      (183.2061 4442.7481) (183.2061 4229.0076) (213.7405 4229.0076)
    ))
    ; P1480 -- see feature_dimensions_mm.csv
    ("05_STONE_JOINTS" 0 (
      (183.2061 4015.2672) (437.4046 4015.2672)
    ))
    ; P1481 -- see feature_dimensions_mm.csv
    ("05_STONE_JOINTS" 0 (
      (183.2061 3801.5267) (606.8702 3801.5267)
    ))
    ; P1482 -- see feature_dimensions_mm.csv
    ("05_STONE_JOINTS" 0 (
      (183.2061 3694.6565) (748.0916 3694.6565)
    ))
    ; P1483 -- see feature_dimensions_mm.csv
    ("05_STONE_JOINTS" 0 (
      (183.2061 3587.7863) (748.0916 3587.7863)
    ))
    ; P1484 -- see feature_dimensions_mm.csv
    ("05_STONE_JOINTS" 0 (
      (183.2061 3374.0458) (578.626 3374.0458)
    ))
    ; P1485 -- see feature_dimensions_mm.csv
    ("05_STONE_JOINTS" 0 (
      (183.2061 3160.3053) (578.626 3160.3053)
    ))
    ; P1486 -- see feature_dimensions_mm.csv
    ("05_STONE_JOINTS" 0 (
      (183.2061 2946.5649) (437.4046 2946.5649)
    ))
    ; P1487 -- see feature_dimensions_mm.csv
    ("05_STONE_JOINTS" 0 (
      (183.2061 2732.8244) (437.4046 2732.8244)
    ))
    ; P1488 -- see feature_dimensions_mm.csv
    ("05_STONE_JOINTS" 0 (
      (183.2061 2305.3435) (578.626 2305.3435)
    ))
    ; P1489 -- see feature_dimensions_mm.csv
    ("05_STONE_JOINTS" 0 (
      (183.2061 2305.3435) (183.2061 2091.6031)
    ))
    ; P1490 -- see feature_dimensions_mm.csv
    ("05_STONE_JOINTS" 0 (
      (183.2061 2305.3435) (183.2061 2519.084) (578.626 2519.084)
    ))
    ; P1491 -- see feature_dimensions_mm.csv
    ("05_STONE_JOINTS" 0 (
      (183.2061 2091.6031) (437.4046 2091.6031)
    ))
    ; P1492 -- see feature_dimensions_mm.csv
    ("05_STONE_JOINTS" 0 (
      (183.2061 2091.6031) (183.2061 1877.8626)
    ))
    ; P1493 -- see feature_dimensions_mm.csv
    ("05_STONE_JOINTS" 0 (
      (183.2061 1877.8626) (437.4046 1877.8626)
    ))
    ; P1494 -- see feature_dimensions_mm.csv
    ("05_STONE_JOINTS" 0 (
      (183.2061 1877.8626) (183.2061 1664.1221)
    ))
    ; P1495 -- see feature_dimensions_mm.csv
    ("05_STONE_JOINTS" 0 (
      (183.2061 1664.1221) (437.4046 1664.1221)
    ))
    ; P1496 -- see feature_dimensions_mm.csv
    ("05_STONE_JOINTS" 0 (
      (183.2061 1664.1221) (183.2061 1450.3817)
    ))
    ; P1497 -- see feature_dimensions_mm.csv
    ("05_STONE_JOINTS" 0 (
      (183.2061 1450.3817) (437.4046 1450.3817)
    ))
    ; P1498 -- see feature_dimensions_mm.csv
    ("05_STONE_JOINTS" 0 (
      (183.2061 1450.3817) (183.2061 1236.6412)
    ))
    ; P1499 -- see feature_dimensions_mm.csv
    ("05_STONE_JOINTS" 0 (
      (183.2061 1236.6412) (437.4046 1236.6412)
    ))
    ; P1500 -- see feature_dimensions_mm.csv
    ("05_STONE_JOINTS" 0 (
      (183.2061 1236.6412) (183.2061 1022.9008)
    ))
    ; P1501 -- see feature_dimensions_mm.csv
    ("05_STONE_JOINTS" 0 (
      (183.2061 1022.9008) (437.4046 1022.9008)
    ))
    ; P1502 -- see feature_dimensions_mm.csv
    ("05_STONE_JOINTS" 0 (
      (183.2061 1022.9008) (183.2061 809.1603) (606.8702 809.1603)
    ))
    ; P1503 -- see feature_dimensions_mm.csv
    ("05_STONE_JOINTS" 0 (
      (296.1832 9358.7786) (606.8702 9358.7786)
    ))
    ; P1504 -- see feature_dimensions_mm.csv
    ("05_STONE_JOINTS" 0 (
      (296.1832 9145.0382) (296.1832 9358.7786)
    ))
    ; P1505 -- see feature_dimensions_mm.csv
    ("05_STONE_JOINTS" 0 (
      (296.1832 9145.0382) (606.8702 9145.0382)
    ))
    ; P1506 -- see feature_dimensions_mm.csv
    ("05_STONE_JOINTS" 0 (
      (296.1832 8503.8168) (889.313 8503.8168)
    ))
    ; P1507 -- see feature_dimensions_mm.csv
    ("05_STONE_JOINTS" 0 (
      (296.1832 8290.0763) (296.1832 8503.8168)
    ))
    ; P1508 -- see feature_dimensions_mm.csv
    ("05_STONE_JOINTS" 0 (
      (296.1832 8290.0763) (606.8702 8290.0763)
    ))
    ; P1509 -- see feature_dimensions_mm.csv
    ("05_STONE_JOINTS" 0 (
      (296.1832 8076.3359) (606.8702 8076.3359)
    ))
    ; P1510 -- see feature_dimensions_mm.csv
    ("05_STONE_JOINTS" 0 (
      (296.1832 7862.5954) (296.1832 8076.3359)
    ))
    ; P1511 -- see feature_dimensions_mm.csv
    ("05_STONE_JOINTS" 0 (
      (296.1832 7862.5954) (793.8931 7862.5954)
    ))
    ; P1512 -- see feature_dimensions_mm.csv
    ("05_STONE_JOINTS" 0 (
      (437.4046 4015.2672) (437.4046 4167.9389)
    ))
    ; P1513 -- see feature_dimensions_mm.csv
    ("05_STONE_JOINTS" 0 (
      (437.4046 4015.2672) (606.8702 4015.2672)
    ))
    ; P1514 -- see feature_dimensions_mm.csv
    ("05_STONE_JOINTS" 0 (
      (437.4046 2946.5649) (889.313 2946.5649)
    ))
    ; P1515 -- see feature_dimensions_mm.csv
    ("05_STONE_JOINTS" 0 (
      (437.4046 2839.6947) (437.4046 2946.5649)
    ))
    ; P1516 -- see feature_dimensions_mm.csv
    ("05_STONE_JOINTS" 0 (
      (437.4046 2839.6947) (961.8321 2839.6947)
    ))
    ; P1517 -- see feature_dimensions_mm.csv
    ("05_STONE_JOINTS" 0 (
      (437.4046 2732.8244) (437.4046 2839.6947)
    ))
    ; P1518 -- see feature_dimensions_mm.csv
    ("05_STONE_JOINTS" 0 (
      (437.4046 2732.8244) (748.0916 2732.8244)
    ))
    ; P1519 -- see feature_dimensions_mm.csv
    ("05_STONE_JOINTS" 0 (
      (437.4046 2091.6031) (748.0916 2091.6031)
    ))
    ; P1520 -- see feature_dimensions_mm.csv
    ("05_STONE_JOINTS" 0 (
      (437.4046 1877.8626) (437.4046 2091.6031)
    ))
    ; P1521 -- see feature_dimensions_mm.csv
    ("05_STONE_JOINTS" 0 (
      (437.4046 1877.8626) (493.8931 1877.8626)
    ))
    ; P1522 -- see feature_dimensions_mm.csv
    ("05_STONE_JOINTS" 0 (
      (437.4046 1664.1221) (493.8931 1664.1221)
    ))
    ; P1523 -- see feature_dimensions_mm.csv
    ("05_STONE_JOINTS" 0 (
      (437.4046 1450.3817) (437.4046 1664.1221)
    ))
    ; P1524 -- see feature_dimensions_mm.csv
    ("05_STONE_JOINTS" 0 (
      (437.4046 1450.3817) (748.0916 1450.3817)
    ))
    ; P1525 -- see feature_dimensions_mm.csv
    ("05_STONE_JOINTS" 0 (
      (437.4046 1236.6412) (748.0916 1236.6412)
    ))
    ; P1526 -- see feature_dimensions_mm.csv
    ("05_STONE_JOINTS" 0 (
      (437.4046 1129.771) (437.4046 1236.6412)
    ))
    ; P1527 -- see feature_dimensions_mm.csv
    ("05_STONE_JOINTS" 0 (
      (437.4046 1129.771) (961.8321 1129.771)
    ))
    ; P1528 -- see feature_dimensions_mm.csv
    ("05_STONE_JOINTS" 0 (
      (437.4046 1022.9008) (437.4046 1129.771)
    ))
    ; P1529 -- see feature_dimensions_mm.csv
    ("05_STONE_JOINTS" 0 (
      (437.4046 1022.9008) (606.8702 1022.9008)
    ))
    ; P1530 -- see feature_dimensions_mm.csv
    ("05_STONE_JOINTS" 0 (
      (493.8931 5816.7939) (493.8931 5847.3282)
    ))
    ; P1531 -- see feature_dimensions_mm.csv
    ("05_STONE_JOINTS" 0 (
      (493.8931 1877.8626) (748.0916 1877.8626)
    ))
    ; P1532 -- see feature_dimensions_mm.csv
    ("05_STONE_JOINTS" 0 (
      (493.8931 1664.1221) (493.8931 1877.8626)
    ))
    ; P1533 -- see feature_dimensions_mm.csv
    ("05_STONE_JOINTS" 0 (
      (493.8931 1664.1221) (748.0916 1664.1221)
    ))
    ; P1534 -- see feature_dimensions_mm.csv
    ("05_STONE_JOINTS" 0 (
      (578.626 8931.2977) (606.8702 8931.2977)
    ))
    ; P1535 -- see feature_dimensions_mm.csv
    ("05_STONE_JOINTS" 0 (
      (578.626 8717.5573) (578.626 8931.2977)
    ))
    ; P1536 -- see feature_dimensions_mm.csv
    ("05_STONE_JOINTS" 0 (
      (578.626 8717.5573) (889.313 8717.5573)
    ))
    ; P1537 -- see feature_dimensions_mm.csv
    ("05_STONE_JOINTS" 0 (
      (578.626 7648.855) (793.8931 7648.855)
    ))
    ; P1538 -- see feature_dimensions_mm.csv
    ("05_STONE_JOINTS" 0 (
      (578.626 7496.1832) (578.626 7648.855)
    ))
    ; P1539 -- see feature_dimensions_mm.csv
    ("05_STONE_JOINTS" 0 (
      (578.626 3374.0458) (793.8931 3374.0458)
    ))
    ; P1540 -- see feature_dimensions_mm.csv
    ("05_STONE_JOINTS" 0 (
      (578.626 3160.3053) (578.626 3374.0458)
    ))
    ; P1541 -- see feature_dimensions_mm.csv
    ("05_STONE_JOINTS" 0 (
      (578.626 3160.3053) (889.313 3160.3053)
    ))
    ; P1542 -- see feature_dimensions_mm.csv
    ("05_STONE_JOINTS" 0 (
      (578.626 2519.084) (748.0916 2519.084)
    ))
    ; P1543 -- see feature_dimensions_mm.csv
    ("05_STONE_JOINTS" 0 (
      (578.626 2305.3435) (578.626 2519.084)
    ))
    ; P1544 -- see feature_dimensions_mm.csv
    ("05_STONE_JOINTS" 0 (
      (578.626 2305.3435) (889.313 2305.3435)
    ))
    ; P1545 -- see feature_dimensions_mm.csv
    ("05_STONE_JOINTS" 0 (
      (1171.7557 9572.5191) (606.8702 9572.5191)
    ))
    ; P1546 -- see feature_dimensions_mm.csv
    ("05_STONE_JOINTS" 0 (
      (606.8702 9465.6489) (606.8702 9557.2519) (606.8702 9572.5191)
    ))
    ; P1547 -- see feature_dimensions_mm.csv
    ("05_STONE_JOINTS" 0 (
      (606.8702 9465.6489) (1171.7557 9465.6489)
    ))
    ; P1548 -- see feature_dimensions_mm.csv
    ("05_STONE_JOINTS" 0 (
      (606.8702 9358.7786) (606.8702 9465.6489)
    ))
    ; P1549 -- see feature_dimensions_mm.csv
    ("05_STONE_JOINTS" 0 (
      (606.8702 9358.7786) (719.8473 9358.7786)
    ))
    ; P1550 -- see feature_dimensions_mm.csv
    ("05_STONE_JOINTS" 0 (
      (606.8702 9145.0382) (719.8473 9145.0382)
    ))
    ; P1551 -- see feature_dimensions_mm.csv
    ("05_STONE_JOINTS" 0 (
      (606.8702 8931.2977) (606.8702 9145.0382)
    ))
    ; P1552 -- see feature_dimensions_mm.csv
    ("05_STONE_JOINTS" 0 (
      (606.8702 8931.2977) (1143.5115 8931.2977)
    ))
    ; P1553 -- see feature_dimensions_mm.csv
    ("05_STONE_JOINTS" 0 (
      (606.8702 8290.0763) (1002.2901 8290.0763)
    ))
    ; P1554 -- see feature_dimensions_mm.csv
    ("05_STONE_JOINTS" 0 (
      (606.8702 8076.3359) (606.8702 8290.0763)
    ))
    ; P1555 -- see feature_dimensions_mm.csv
    ("05_STONE_JOINTS" 0 (
      (606.8702 8076.3359) (793.8931 8076.3359) (793.8931 7862.5954)
    ))
    ; P1556 -- see feature_dimensions_mm.csv
    ("05_STONE_JOINTS" 0 (
      (606.8702 4015.2672) (861.0687 4015.2672)
    ))
    ; P1557 -- see feature_dimensions_mm.csv
    ("05_STONE_JOINTS" 0 (
      (606.8702 3801.5267) (606.8702 4015.2672)
    ))
    ; P1558 -- see feature_dimensions_mm.csv
    ("05_STONE_JOINTS" 0 (
      (606.8702 3801.5267) (748.0916 3801.5267)
    ))
    ; P1559 -- see feature_dimensions_mm.csv
    ("05_STONE_JOINTS" 0 (
      (606.8702 1022.9008) (917.5573 1022.9008)
    ))
    ; P1560 -- see feature_dimensions_mm.csv
    ("05_STONE_JOINTS" 0 (
      (606.8702 809.1603) (606.8702 1022.9008)
    ))
    ; P1561 -- see feature_dimensions_mm.csv
    ("05_STONE_JOINTS" 0 (
      (606.8702 809.1603) (917.5573 809.1603) (917.5573 1022.9008)
    ))
    ; P1562 -- see feature_dimensions_mm.csv
    ("05_STONE_JOINTS" 0 (
      (719.8473 9358.7786) (1171.7557 9358.7786)
    ))
    ; P1563 -- see feature_dimensions_mm.csv
    ("05_STONE_JOINTS" 0 (
      (719.8473 9145.0382) (719.8473 9358.7786)
    ))
    ; P1564 -- see feature_dimensions_mm.csv
    ("05_STONE_JOINTS" 0 (
      (719.8473 9145.0382) (1171.7557 9145.0382)
    ))
    ; P1565 -- see feature_dimensions_mm.csv
    ("05_STONE_JOINTS" 0 (
      (748.0916 3801.5267) (961.8321 3801.5267)
    ))
    ; P1566 -- see feature_dimensions_mm.csv
    ("05_STONE_JOINTS" 0 (
      (748.0916 3694.6565) (748.0916 3801.5267)
    ))
    ; P1567 -- see feature_dimensions_mm.csv
    ("05_STONE_JOINTS" 0 (
      (748.0916 3587.7863) (748.0916 3694.6565)
    ))
    ; P1568 -- see feature_dimensions_mm.csv
    ("05_STONE_JOINTS" 0 (
      (748.0916 3587.7863) (793.8931 3587.7863)
    ))
    ; P1569 -- see feature_dimensions_mm.csv
    ("05_STONE_JOINTS" 0 (
      (748.0916 2732.8244) (961.8321 2732.8244)
    ))
    ; P1570 -- see feature_dimensions_mm.csv
    ("05_STONE_JOINTS" 0 (
      (748.0916 2519.084) (748.0916 2732.8244)
    ))
    ; P1571 -- see feature_dimensions_mm.csv
    ("05_STONE_JOINTS" 0 (
      (748.0916 2519.084) (889.313 2519.084)
    ))
    ; P1572 -- see feature_dimensions_mm.csv
    ("05_STONE_JOINTS" 0 (
      (748.0916 2091.6031) (889.313 2091.6031)
    ))
    ; P1573 -- see feature_dimensions_mm.csv
    ("05_STONE_JOINTS" 0 (
      (748.0916 1877.8626) (748.0916 2091.6031)
    ))
    ; P1574 -- see feature_dimensions_mm.csv
    ("05_STONE_JOINTS" 0 (
      (748.0916 1877.8626) (917.5573 1877.8626)
    ))
    ; P1575 -- see feature_dimensions_mm.csv
    ("05_STONE_JOINTS" 0 (
      (748.0916 1664.1221) (917.5573 1664.1221)
    ))
    ; P1576 -- see feature_dimensions_mm.csv
    ("05_STONE_JOINTS" 0 (
      (748.0916 1450.3817) (748.0916 1664.1221)
    ))
    ; P1577 -- see feature_dimensions_mm.csv
    ("05_STONE_JOINTS" 0 (
      (748.0916 1450.3817) (961.8321 1450.3817)
    ))
    ; P1578 -- see feature_dimensions_mm.csv
    ("05_STONE_JOINTS" 0 (
      (748.0916 1236.6412) (748.0916 1450.3817)
    ))
    ; P1579 -- see feature_dimensions_mm.csv
    ("05_STONE_JOINTS" 0 (
      (748.0916 1236.6412) (961.8321 1236.6412)
    ))
    ; P1580 -- see feature_dimensions_mm.csv
    ("05_STONE_JOINTS" 0 (
      (793.8931 7648.855) (793.8931 7740.458) (793.8931 7862.5954)
    ))
    ; P1581 -- see feature_dimensions_mm.csv
    ("05_STONE_JOINTS" 0 (
      (961.8321 7541.9847) (793.8931 7541.9847) (793.8931 7648.855)
    ))
    ; P1582 -- see feature_dimensions_mm.csv
    ("05_STONE_JOINTS" 0 (
      (861.0687 4015.2672) (861.0687 4167.9389)
    ))
    ; P1583 -- see feature_dimensions_mm.csv
    ("05_STONE_JOINTS" 0 (
      (861.0687 4015.2672) (961.8321 4015.2672)
    ))
    ; P1584 -- see feature_dimensions_mm.csv
    ("05_STONE_JOINTS" 0 (
      (889.313 8717.5573) (1143.5115 8717.5573)
    ))
    ; P1585 -- see feature_dimensions_mm.csv
    ("05_STONE_JOINTS" 0 (
      (889.313 8503.8168) (889.313 8717.5573)
    ))
    ; P1586 -- see feature_dimensions_mm.csv
    ("05_STONE_JOINTS" 0 (
      (889.313 8503.8168) (1002.2901 8503.8168)
    ))
    ; P1587 -- see feature_dimensions_mm.csv
    ("05_STONE_JOINTS" 0 (
      (889.313 3160.3053) (889.313 3267.1756)
    ))
    ; P1588 -- see feature_dimensions_mm.csv
    ("05_STONE_JOINTS" 0 (
      (889.313 3160.3053) (961.8321 3160.3053)
    ))
    ; P1589 -- see feature_dimensions_mm.csv
    ("05_STONE_JOINTS" 0 (
      (889.313 2946.5649) (889.313 3160.3053)
    ))
    ; P1590 -- see feature_dimensions_mm.csv
    ("05_STONE_JOINTS" 0 (
      (889.313 2946.5649) (961.8321 2946.5649)
    ))
    ; P1591 -- see feature_dimensions_mm.csv
    ("05_STONE_JOINTS" 0 (
      (889.313 2519.084) (961.8321 2519.084) (961.8321 2412.2137)
    ))
    ; P1592 -- see feature_dimensions_mm.csv
    ("05_STONE_JOINTS" 0 (
      (889.313 2412.2137) (889.313 2519.084)
    ))
    ; P1593 -- see feature_dimensions_mm.csv
    ("05_STONE_JOINTS" 0 (
      (889.313 2412.2137) (961.8321 2412.2137)
    ))
    ; P1594 -- see feature_dimensions_mm.csv
    ("05_STONE_JOINTS" 0 (
      (889.313 2305.3435) (889.313 2412.2137)
    ))
    ; P1595 -- see feature_dimensions_mm.csv
    ("05_STONE_JOINTS" 0 (
      (889.313 2305.3435) (961.8321 2305.3435)
    ))
    ; P1596 -- see feature_dimensions_mm.csv
    ("05_STONE_JOINTS" 0 (
      (889.313 2091.6031) (889.313 2305.3435)
    ))
    ; P1597 -- see feature_dimensions_mm.csv
    ("05_STONE_JOINTS" 0 (
      (889.313 2091.6031) (961.8321 2091.6031)
    ))
    ; P1598 -- see feature_dimensions_mm.csv
    ("05_STONE_JOINTS" 0 (
      (900.7634 7435.1145) (961.8321 7435.1145)
    ))
    ; P1599 -- see feature_dimensions_mm.csv
    ("05_STONE_JOINTS" 0 (
      (900.7634 7221.374) (961.8321 7221.374)
    ))
    ; P1600 -- see feature_dimensions_mm.csv
    ("05_STONE_JOINTS" 0 (
      (900.7634 7114.5038) (961.8321 7114.5038)
    ))
    ; P1601 -- see feature_dimensions_mm.csv
    ("05_STONE_JOINTS" 0 (
      (900.7634 6793.8931) (946.5649 6793.8931) (961.8321 6793.8931)
    ))
    ; P1602 -- see feature_dimensions_mm.csv
    ("05_STONE_JOINTS" 0 (
      (900.7634 6793.8931) (900.7634 6580.1527)
    ))
    ; P1603 -- see feature_dimensions_mm.csv
    ("05_STONE_JOINTS" 0 (
      (900.7634 6793.8931) (900.7634 7007.6336) (961.8321 7007.6336)
    ))
    ; P1604 -- see feature_dimensions_mm.csv
    ("05_STONE_JOINTS" 0 (
      (900.7634 6580.1527) (946.5649 6580.1527) (961.8321 6580.1527)
    ))
    ; P1605 -- see feature_dimensions_mm.csv
    ("05_STONE_JOINTS" 0 (
      (900.7634 6580.1527) (900.7634 6366.4122)
    ))
    ; P1606 -- see feature_dimensions_mm.csv
    ("05_STONE_JOINTS" 0 (
      (900.7634 6366.4122) (961.8321 6366.4122)
    ))
    ; P1607 -- see feature_dimensions_mm.csv
    ("05_STONE_JOINTS" 0 (
      (900.7634 6366.4122) (900.7634 6259.542)
    ))
    ; P1608 -- see feature_dimensions_mm.csv
    ("05_STONE_JOINTS" 0 (
      (900.7634 6259.542) (961.8321 6259.542)
    ))
    ; P1609 -- see feature_dimensions_mm.csv
    ("05_STONE_JOINTS" 0 (
      (900.7634 6259.542) (900.7634 6152.6718)
    ))
    ; P1610 -- see feature_dimensions_mm.csv
    ("05_STONE_JOINTS" 0 (
      (900.7634 6152.6718) (961.8321 6152.6718)
    ))
    ; P1611 -- see feature_dimensions_mm.csv
    ("05_STONE_JOINTS" 0 (
      (900.7634 6152.6718) (900.7634 5938.9313)
    ))
    ; P1612 -- see feature_dimensions_mm.csv
    ("05_STONE_JOINTS" 0 (
      (900.7634 5938.9313) (961.8321 5938.9313)
    ))
    ; P1613 -- see feature_dimensions_mm.csv
    ("05_STONE_JOINTS" 0 (
      (900.7634 5938.9313) (900.7634 5847.3282)
    ))
    ; P1614 -- see feature_dimensions_mm.csv
    ("05_STONE_JOINTS" 0 (
      (900.7634 5816.7939) (900.7634 5725.1908)
    ))
    ; P1615 -- see feature_dimensions_mm.csv
    ("05_STONE_JOINTS" 0 (
      (900.7634 5725.1908) (961.8321 5725.1908)
    ))
    ; P1616 -- see feature_dimensions_mm.csv
    ("05_STONE_JOINTS" 0 (
      (900.7634 5725.1908) (900.7634 5511.4504)
    ))
    ; P1617 -- see feature_dimensions_mm.csv
    ("05_STONE_JOINTS" 0 (
      (900.7634 5511.4504) (961.8321 5511.4504)
    ))
    ; P1618 -- see feature_dimensions_mm.csv
    ("05_STONE_JOINTS" 0 (
      (900.7634 5511.4504) (900.7634 5297.7099)
    ))
    ; P1619 -- see feature_dimensions_mm.csv
    ("05_STONE_JOINTS" 0 (
      (900.7634 5297.7099) (917.5573 5297.7099)
    ))
    ; P1620 -- see feature_dimensions_mm.csv
    ("05_STONE_JOINTS" 0 (
      (900.7634 5297.7099) (900.7634 5083.9695) (917.5573 5083.9695)
    ))
    ; P1621 -- see feature_dimensions_mm.csv
    ("05_STONE_JOINTS" 0 (
      (900.7634 4870.229) (961.8321 4870.229)
    ))
    ; P1622 -- see feature_dimensions_mm.csv
    ("05_STONE_JOINTS" 0 (
      (900.7634 4763.3588) (961.8321 4763.3588)
    ))
    ; P1623 -- see feature_dimensions_mm.csv
    ("05_STONE_JOINTS" 0 (
      (900.7634 4656.4885) (961.8321 4656.4885)
    ))
    ; P1624 -- see feature_dimensions_mm.csv
    ("05_STONE_JOINTS" 0 (
      (900.7634 4549.6183) (961.8321 4549.6183) (961.8321 4656.4885)
    ))
    ; P1625 -- see feature_dimensions_mm.csv
    ("05_STONE_JOINTS" 0 (
      (900.7634 4442.7481) (917.5573 4442.7481)
    ))
    ; P1626 -- see feature_dimensions_mm.csv
    ("05_STONE_JOINTS" 0 (
      (900.7634 4229.0076) (917.5573 4229.0076)
    ))
    ; P1627 -- see feature_dimensions_mm.csv
    ("05_STONE_JOINTS" 0 (
      (917.5573 5297.7099) (961.8321 5297.7099) (961.8321 5083.9695)
    ))
    ; P1628 -- see feature_dimensions_mm.csv
    ("05_STONE_JOINTS" 0 (
      (917.5573 5083.9695) (917.5573 5297.7099)
    ))
    ; P1629 -- see feature_dimensions_mm.csv
    ("05_STONE_JOINTS" 0 (
      (917.5573 5083.9695) (961.8321 5083.9695)
    ))
    ; P1630 -- see feature_dimensions_mm.csv
    ("05_STONE_JOINTS" 0 (
      (917.5573 4442.7481) (961.8321 4442.7481)
    ))
    ; P1631 -- see feature_dimensions_mm.csv
    ("05_STONE_JOINTS" 0 (
      (917.5573 4229.0076) (917.5573 4442.7481)
    ))
    ; P1632 -- see feature_dimensions_mm.csv
    ("05_STONE_JOINTS" 0 (
      (917.5573 4229.0076) (961.8321 4229.0076)
    ))
    ; P1633 -- see feature_dimensions_mm.csv
    ("05_STONE_JOINTS" 0 (
      (917.5573 1877.8626) (961.8321 1877.8626)
    ))
    ; P1634 -- see feature_dimensions_mm.csv
    ("05_STONE_JOINTS" 0 (
      (917.5573 1664.1221) (917.5573 1877.8626)
    ))
    ; P1635 -- see feature_dimensions_mm.csv
    ("05_STONE_JOINTS" 0 (
      (917.5573 1664.1221) (961.8321 1664.1221)
    ))
    ; P1636 -- see feature_dimensions_mm.csv
    ("05_STONE_JOINTS" 0 (
      (917.5573 1022.9008) (961.8321 1022.9008)
    ))
    ; P1637 -- see feature_dimensions_mm.csv
    ("05_STONE_JOINTS" 0 (
      (4992.3664 7541.9847) (961.8321 7541.9847)
    ))
    ; P1638 -- see feature_dimensions_mm.csv
    ("05_STONE_JOINTS" 0 (
      (961.8321 7541.9847) (961.8321 7526.7176) (4992.3664 7526.7176)
    ))
    ; P1639 -- see feature_dimensions_mm.csv
    ("05_STONE_JOINTS" 0 (
      (961.8321 6992.3664) (4992.3664 6992.3664)
    ))
    ; P1640 -- see feature_dimensions_mm.csv
    ("05_STONE_JOINTS" 0 (
      (4992.3664 6564.8855) (961.8321 6564.8855)
    ))
    ; P1641 -- see feature_dimensions_mm.csv
    ("05_STONE_JOINTS" 0 (
      (961.8321 5969.4656) (1358.7786 5969.4656) (1358.7786 5816.7939)
    ))
    ; P1642 -- see feature_dimensions_mm.csv
    ("05_STONE_JOINTS" 0 (
      (961.8321 4870.229) (961.8321 5083.9695)
    ))
    ; P1643 -- see feature_dimensions_mm.csv
    ("05_STONE_JOINTS" 0 (
      (961.8321 4763.3588) (961.8321 4870.229)
    ))
    ; P1644 -- see feature_dimensions_mm.csv
    ("05_STONE_JOINTS" 0 (
      (961.8321 4656.4885) (961.8321 4763.3588)
    ))
    ; P1645 -- see feature_dimensions_mm.csv
    ("05_STONE_JOINTS" 0 (
      (4992.3664 3267.1756) (961.8321 3267.1756)
    ))
    ; P1646 -- see feature_dimensions_mm.csv
    ("05_STONE_JOINTS" 0 (
      (961.8321 2961.8321) (1938.9313 2961.8321)
    ))
    ; P1647 -- see feature_dimensions_mm.csv
    ("05_STONE_JOINTS" 0 (
      (961.8321 2641.2214) (4992.3664 2641.2214)
    ))
    ; P1648 -- see feature_dimensions_mm.csv
    ("05_STONE_JOINTS" 0 (
      (961.8321 2412.2137) (961.8321 2305.3435)
    ))
    ; P1649 -- see feature_dimensions_mm.csv
    ("05_STONE_JOINTS" 0 (
      (961.8321 2305.3435) (1863.4351 2305.3435)
    ))
    ; P1650 -- see feature_dimensions_mm.csv
    ("05_STONE_JOINTS" 0 (
      (961.8321 2305.3435) (961.8321 2091.6031)
    ))
    ; P1651 -- see feature_dimensions_mm.csv
    ("05_STONE_JOINTS" 0 (
      (961.8321 2091.6031) (961.8321 1984.7328) (1325.6947 1984.7328)
    ))
    ; P1652 -- see feature_dimensions_mm.csv
    ("05_STONE_JOINTS" 0 (
      (961.8321 1633.5878) (1435.1145 1633.5878)
    ))
    ; P1653 -- see feature_dimensions_mm.csv
    ("05_STONE_JOINTS" 0 (
      (961.8321 1282.4427) (1435.1145 1282.4427)
    ))
    ; P1654 -- see feature_dimensions_mm.csv
    ("05_STONE_JOINTS" 0 (
      (961.8321 931.2977) (1435.1145 931.2977) (1435.1145 656.4885)
    ))
    ; P1655 -- see feature_dimensions_mm.csv
    ("05_STONE_JOINTS" 0 (
      (1002.2901 8503.8168) (1312.9771 8503.8168)
    ))
    ; P1656 -- see feature_dimensions_mm.csv
    ("05_STONE_JOINTS" 0 (
      (1002.2901 8290.0763) (1002.2901 8503.8168)
    ))
    ; P1657 -- see feature_dimensions_mm.csv
    ("05_STONE_JOINTS" 0 (
      (1002.2901 8290.0763) (1171.7557 8290.0763)
    ))
    ; P1658 -- see feature_dimensions_mm.csv
    ("05_STONE_JOINTS" 0 (
      (1143.5115 8931.2977) (1171.7557 8931.2977)
    ))
    ; P1659 -- see feature_dimensions_mm.csv
    ("05_STONE_JOINTS" 0 (
      (1143.5115 8717.5573) (1143.5115 8931.2977)
    ))
    ; P1660 -- see feature_dimensions_mm.csv
    ("05_STONE_JOINTS" 0 (
      (1143.5115 8717.5573) (1312.9771 8717.5573)
    ))
    ; P1661 -- see feature_dimensions_mm.csv
    ("05_STONE_JOINTS" 0 (
      (1736.6412 9572.5191) (1171.7557 9572.5191)
    ))
    ; P1662 -- see feature_dimensions_mm.csv
    ("05_STONE_JOINTS" 0 (
      (1171.7557 9465.6489) (1171.7557 9557.2519) (1171.7557 9572.5191)
    ))
    ; P1663 -- see feature_dimensions_mm.csv
    ("05_STONE_JOINTS" 0 (
      (1171.7557 9358.7786) (1171.7557 9465.6489)
    ))
    ; P1664 -- see feature_dimensions_mm.csv
    ("05_STONE_JOINTS" 0 (
      (1171.7557 9358.7786) (1425.9542 9358.7786)
    ))
    ; P1665 -- see feature_dimensions_mm.csv
    ("05_STONE_JOINTS" 0 (
      (1171.7557 9145.0382) (1206.1069 9145.0382) (1206.1069 9312.9771) (1404.5802 9312.9771) (1404.5802 9145.0382)
      (1425.9542 9145.0382)
    ))
    ; P1666 -- see feature_dimensions_mm.csv
    ("05_STONE_JOINTS" 0 (
      (1171.7557 8931.2977) (1171.7557 9145.0382)
    ))
    ; P1667 -- see feature_dimensions_mm.csv
    ("05_STONE_JOINTS" 0 (
      (1171.7557 8931.2977) (1482.4427 8931.2977)
    ))
    ; P1668 -- see feature_dimensions_mm.csv
    ("05_STONE_JOINTS" 0 (
      (1171.7557 8290.0763) (1425.9542 8290.0763)
    ))
    ; P1669 -- see feature_dimensions_mm.csv
    ("05_STONE_JOINTS" 0 (
      (1171.7557 8076.3359) (1171.7557 8290.0763)
    ))
    ; P1670 -- see feature_dimensions_mm.csv
    ("05_STONE_JOINTS" 0 (
      (1312.9771 8717.5573) (1567.1756 8717.5573)
    ))
    ; P1671 -- see feature_dimensions_mm.csv
    ("05_STONE_JOINTS" 0 (
      (1312.9771 8503.8168) (1312.9771 8717.5573)
    ))
    ; P1672 -- see feature_dimensions_mm.csv
    ("05_STONE_JOINTS" 0 (
      (1312.9771 8503.8168) (1425.9542 8503.8168)
    ))
    ; P1673 -- see feature_dimensions_mm.csv
    ("05_STONE_JOINTS" 0 (
      (1343.5115 1969.4656) (1325.6947 1984.7328)
    ))
    ; P1674 -- see feature_dimensions_mm.csv
    ("05_STONE_JOINTS" 0 (
      (1325.6947 1984.7328) (1236.6412 2061.0687) (1684.4122 2061.0687)
    ))
    ; P1675 -- see feature_dimensions_mm.csv
    ("05_STONE_JOINTS" 0 (
      (1425.9542 9358.7786) (1736.6412 9358.7786)
    ))
    ; P1676 -- see feature_dimensions_mm.csv
    ("05_STONE_JOINTS" 0 (
      (1425.9542 9145.0382) (1425.9542 9358.7786)
    ))
    ; P1677 -- see feature_dimensions_mm.csv
    ("05_STONE_JOINTS" 0 (
      (1425.9542 9145.0382) (1482.4427 9145.0382)
    ))
    ; P1678 -- see feature_dimensions_mm.csv
    ("05_STONE_JOINTS" 0 (
      (1425.9542 8503.8168) (1736.6412 8503.8168)
    ))
    ; P1679 -- see feature_dimensions_mm.csv
    ("05_STONE_JOINTS" 0 (
      (1425.9542 8290.0763) (1425.9542 8503.8168)
    ))
    ; P1680 -- see feature_dimensions_mm.csv
    ("05_STONE_JOINTS" 0 (
      (1425.9542 8290.0763) (1736.6412 8290.0763)
    ))
    ; P1681 -- see feature_dimensions_mm.csv
    ("05_STONE_JOINTS" 0 (
      (1482.4427 9145.0382) (1694.6565 9145.0382)
    ))
    ; P1682 -- see feature_dimensions_mm.csv
    ("05_STONE_JOINTS" 0 (
      (1482.4427 9038.1679) (1482.4427 9145.0382)
    ))
    ; P1683 -- see feature_dimensions_mm.csv
    ("05_STONE_JOINTS" 0 (
      (1482.4427 9038.1679) (1694.6565 9038.1679)
    ))
    ; P1684 -- see feature_dimensions_mm.csv
    ("05_STONE_JOINTS" 0 (
      (1482.4427 8931.2977) (1482.4427 9038.1679)
    ))
    ; P1685 -- see feature_dimensions_mm.csv
    ("05_STONE_JOINTS" 0 (
      (1482.4427 8931.2977) (1567.1756 8931.2977)
    ))
    ; P1686 -- see feature_dimensions_mm.csv
    ("05_STONE_JOINTS" 0 (
      (1567.1756 8931.2977) (1877.8626 8931.2977)
    ))
    ; P1687 -- see feature_dimensions_mm.csv
    ("05_STONE_JOINTS" 0 (
      (1567.1756 8717.5573) (1567.1756 8931.2977)
    ))
    ; P1688 -- see feature_dimensions_mm.csv
    ("05_STONE_JOINTS" 0 (
      (1567.1756 8717.5573) (1736.6412 8717.5573)
    ))
    ; P1689 -- see feature_dimensions_mm.csv
    ("05_STONE_JOINTS" 0 (
      (1730.6718 2155.7252) (1711.8321 2122.5954) (1695.3435 2088.3817)
    ))
    ; P1690 -- see feature_dimensions_mm.csv
    ("05_STONE_JOINTS" 0 (
      (2047.3282 9572.5191) (1736.6412 9572.5191)
    ))
    ; P1691 -- see feature_dimensions_mm.csv
    ("05_STONE_JOINTS" 0 (
      (1736.6412 9358.7786) (1736.6412 9557.2519) (1736.6412 9572.5191)
    ))
    ; P1692 -- see feature_dimensions_mm.csv
    ("05_STONE_JOINTS" 0 (
      (1736.6412 9358.7786) (2047.3282 9358.7786)
    ))
    ; P1693 -- see feature_dimensions_mm.csv
    ("05_STONE_JOINTS" 0 (
      (1736.6412 8717.5573) (1877.8626 8717.5573)
    ))
    ; P1694 -- see feature_dimensions_mm.csv
    ("05_STONE_JOINTS" 0 (
      (1736.6412 8503.8168) (1736.6412 8717.5573)
    ))
    ; P1695 -- see feature_dimensions_mm.csv
    ("05_STONE_JOINTS" 0 (
      (1736.6412 8503.8168) (2160.3053 8503.8168)
    ))
    ; P1696 -- see feature_dimensions_mm.csv
    ("05_STONE_JOINTS" 0 (
      (1736.6412 8290.0763) (1736.6412 8503.8168)
    ))
    ; P1697 -- see feature_dimensions_mm.csv
    ("05_STONE_JOINTS" 0 (
      (1736.6412 8290.0763) (2047.3282 8290.0763)
    ))
    ; P1698 -- see feature_dimensions_mm.csv
    ("05_STONE_JOINTS" 0 (
      (1736.6412 8076.3359) (1736.6412 8290.0763)
    ))
    ; P1699 -- see feature_dimensions_mm.csv
    ("05_STONE_JOINTS" 0 (
      (1863.4351 2305.3435) (1856.8855 2300.2901) (1827.7252 2274.6107) (1800.3969 2247.1908) (1775.0534 2218.1527)
      (1751.771 2187.6183)
    ))
    ; P1700 -- see feature_dimensions_mm.csv
    ("05_STONE_JOINTS" 0 (
      (1887.7863 2324.1221) (1863.4351 2305.3435)
    ))
    ; P1701 -- see feature_dimensions_mm.csv
    ("05_STONE_JOINTS" 0 (
      (1877.8626 8931.2977) (2188.5496 8931.2977)
    ))
    ; P1702 -- see feature_dimensions_mm.csv
    ("05_STONE_JOINTS" 0 (
      (1877.8626 8717.5573) (1877.8626 8931.2977)
    ))
    ; P1703 -- see feature_dimensions_mm.csv
    ("05_STONE_JOINTS" 0 (
      (1877.8626 8717.5573) (2188.5496 8717.5573)
    ))
    ; P1704 -- see feature_dimensions_mm.csv
    ("05_STONE_JOINTS" 0 (
      (1893.1298 9145.0382) (2132.0611 9145.0382)
    ))
    ; P1705 -- see feature_dimensions_mm.csv
    ("05_STONE_JOINTS" 0 (
      (1893.1298 9038.1679) (2167.9389 9038.1679)
    ))
    ; P1706 -- see feature_dimensions_mm.csv
    ("05_STONE_JOINTS" 0 (
      (1954.1985 2365.8473) (1920.2595 2346.0)
    ))
    ; P1707 -- see feature_dimensions_mm.csv
    ("05_STONE_JOINTS" 0 (
      (2150.1985 2433.2366) (2140.3969 2431.7252) (2101.4809 2423.1908) (2063.2366 2412.2901) (2025.8473 2399.0534)
      (1989.4351 2383.542)
    ))
    ; P1708 -- see feature_dimensions_mm.csv
    ("05_STONE_JOINTS" 0 (
      (2358.0153 9572.5191) (2047.3282 9572.5191)
    ))
    ; P1709 -- see feature_dimensions_mm.csv
    ("05_STONE_JOINTS" 0 (
      (2047.3282 9358.7786) (2047.3282 9557.2519) (2047.3282 9572.5191)
    ))
    ; P1710 -- see feature_dimensions_mm.csv
    ("05_STONE_JOINTS" 0 (
      (2047.3282 9358.7786) (2132.0611 9358.7786)
    ))
    ; P1711 -- see feature_dimensions_mm.csv
    ("05_STONE_JOINTS" 0 (
      (2047.3282 8290.0763) (2160.3053 8290.0763)
    ))
    ; P1712 -- see feature_dimensions_mm.csv
    ("05_STONE_JOINTS" 0 (
      (2047.3282 8076.3359) (2047.3282 8290.0763)
    ))
    ; P1713 -- see feature_dimensions_mm.csv
    ("05_STONE_JOINTS" 0 (
      (2061.0687 2961.8321) (2229.0076 2961.8321)
    ))
    ; P1714 -- see feature_dimensions_mm.csv
    ("05_STONE_JOINTS" 0 (
      (2132.0611 9358.7786) (2358.0153 9358.7786)
    ))
    ; P1715 -- see feature_dimensions_mm.csv
    ("05_STONE_JOINTS" 0 (
      (2132.0611 9145.0382) (2132.0611 9358.7786)
    ))
    ; P1716 -- see feature_dimensions_mm.csv
    ("05_STONE_JOINTS" 0 (
      (2132.0611 9145.0382) (2167.9389 9145.0382)
    ))
    ; P1717 -- see feature_dimensions_mm.csv
    ("05_STONE_JOINTS" 0 (
      (2160.3053 8503.8168) (2301.5267 8503.8168)
    ))
    ; P1718 -- see feature_dimensions_mm.csv
    ("05_STONE_JOINTS" 0 (
      (2160.3053 8290.0763) (2160.3053 8503.8168)
    ))
    ; P1719 -- see feature_dimensions_mm.csv
    ("05_STONE_JOINTS" 0 (
      (2160.3053 8290.0763) (2358.0153 8290.0763)
    ))
    ; P1720 -- see feature_dimensions_mm.csv
    ("05_STONE_JOINTS" 0 (
      (2188.5496 8931.2977) (2188.5496 8946.5649)
    ))
    ; P1721 -- see feature_dimensions_mm.csv
    ("05_STONE_JOINTS" 0 (
      (2188.5496 8931.2977) (2612.2137 8931.2977)
    ))
    ; P1722 -- see feature_dimensions_mm.csv
    ("05_STONE_JOINTS" 0 (
      (2188.5496 8717.5573) (2188.5496 8931.2977)
    ))
    ; P1723 -- see feature_dimensions_mm.csv
    ("05_STONE_JOINTS" 0 (
      (2188.5496 8717.5573) (2301.5267 8717.5573)
    ))
    ; P1724 -- see feature_dimensions_mm.csv
    ("05_STONE_JOINTS" 0 (
      (2301.5267 8717.5573) (2612.2137 8717.5573)
    ))
    ; P1725 -- see feature_dimensions_mm.csv
    ("05_STONE_JOINTS" 0 (
      (2301.5267 8503.8168) (2301.5267 8717.5573)
    ))
    ; P1726 -- see feature_dimensions_mm.csv
    ("05_STONE_JOINTS" 0 (
      (2301.5267 8503.8168) (2470.9924 8503.8168)
    ))
    ; P1727 -- see feature_dimensions_mm.csv
    ("05_STONE_JOINTS" 0 (
      (2351.145 2961.8321) (2519.084 2961.8321)
    ))
    ; P1728 -- see feature_dimensions_mm.csv
    ("05_STONE_JOINTS" 0 (
      (3064.1221 9572.5191) (2358.0153 9572.5191)
    ))
    ; P1729 -- see feature_dimensions_mm.csv
    ("05_STONE_JOINTS" 0 (
      (2358.0153 9358.7786) (2358.0153 9557.2519) (2358.0153 9572.5191)
    ))
    ; P1730 -- see feature_dimensions_mm.csv
    ("05_STONE_JOINTS" 0 (
      (2358.0153 9358.7786) (2442.7481 9358.7786)
    ))
    ; P1731 -- see feature_dimensions_mm.csv
    ("05_STONE_JOINTS" 0 (
      (2358.0153 8290.0763) (2470.9924 8290.0763)
    ))
    ; P1732 -- see feature_dimensions_mm.csv
    ("05_STONE_JOINTS" 0 (
      (2358.0153 8076.3359) (2358.0153 8290.0763)
    ))
    ; P1733 -- see feature_dimensions_mm.csv
    ("05_STONE_JOINTS" 0 (
      (2366.4122 9145.0382) (2442.7481 9145.0382)
    ))
    ; P1734 -- see feature_dimensions_mm.csv
    ("05_STONE_JOINTS" 0 (
      (2655.6489 2305.3435) (2631.2977 2324.1221) (2598.8244 2346.0) (2564.8855 2365.8473) (2529.6489 2383.542)
      (2493.2366 2399.0534) (2455.8473 2412.2901) (2417.6031 2423.1908)
    ))
    ; P1735 -- see feature_dimensions_mm.csv
    ("05_STONE_JOINTS" 0 (
      (2442.7481 9358.7786) (2866.4122 9358.7786)
    ))
    ; P1736 -- see feature_dimensions_mm.csv
    ("05_STONE_JOINTS" 0 (
      (2442.7481 9145.0382) (2442.7481 9358.7786)
    ))
    ; P1737 -- see feature_dimensions_mm.csv
    ("05_STONE_JOINTS" 0 (
      (2442.7481 9145.0382) (2612.2137 9145.0382)
    ))
    ; P1738 -- see feature_dimensions_mm.csv
    ("05_STONE_JOINTS" 0 (
      (2470.9924 8503.8168) (2612.2137 8503.8168)
    ))
    ; P1739 -- see feature_dimensions_mm.csv
    ("05_STONE_JOINTS" 0 (
      (2470.9924 8290.0763) (2470.9924 8503.8168)
    ))
    ; P1740 -- see feature_dimensions_mm.csv
    ("05_STONE_JOINTS" 0 (
      (2470.9924 8290.0763) (3035.8779 8290.0763)
    ))
    ; P1741 -- see feature_dimensions_mm.csv
    ("05_STONE_JOINTS" 0 (
      (2612.2137 9145.0382) (2641.2214 9145.0382)
    ))
    ; P1742 -- see feature_dimensions_mm.csv
    ("05_STONE_JOINTS" 0 (
      (2612.2137 8931.2977) (2612.2137 9145.0382)
    ))
    ; P1743 -- see feature_dimensions_mm.csv
    ("05_STONE_JOINTS" 0 (
      (2612.2137 8931.2977) (2753.4351 8931.2977)
    ))
    ; P1744 -- see feature_dimensions_mm.csv
    ("05_STONE_JOINTS" 0 (
      (2612.2137 8717.5573) (2753.4351 8717.5573)
    ))
    ; P1745 -- see feature_dimensions_mm.csv
    ("05_STONE_JOINTS" 0 (
      (2612.2137 8610.687) (2612.2137 8717.5573)
    ))
    ; P1746 -- see feature_dimensions_mm.csv
    ("05_STONE_JOINTS" 0 (
      (2612.2137 8610.687) (3318.3206 8610.687)
    ))
    ; P1747 -- see feature_dimensions_mm.csv
    ("05_STONE_JOINTS" 0 (
      (2612.2137 8503.8168) (2612.2137 8610.687)
    ))
    ; P1748 -- see feature_dimensions_mm.csv
    ("05_STONE_JOINTS" 0 (
      (2612.2137 8503.8168) (3035.8779 8503.8168)
    ))
    ; P1749 -- see feature_dimensions_mm.csv
    ("05_STONE_JOINTS" 0 (
      (2839.6947 9145.0382) (2839.6947 8946.5649) (2641.2214 8946.5649) (2641.2214 9145.0382)
    ))
    ; P1750 -- see feature_dimensions_mm.csv
    ("05_STONE_JOINTS" 0 (
      (2641.2214 9145.0382) (2641.2214 9312.9771) (2839.6947 9312.9771) (2839.6947 9145.0382)
    ))
    ; P1751 -- see feature_dimensions_mm.csv
    ("05_STONE_JOINTS" 0 (
      (2641.2214 2961.8321) (3343.5115 2961.8321)
    ))
    ; P1752 -- see feature_dimensions_mm.csv
    ("05_STONE_JOINTS" 0 (
      (2655.6489 2305.3435) (3314.6718 2305.3435)
    ))
    ; P1753 -- see feature_dimensions_mm.csv
    ("05_STONE_JOINTS" 0 (
      (2788.4122 2155.7252) (2767.313 2187.6183) (2744.0305 2218.1527) (2718.687 2247.1908) (2691.3588 2274.6107)
      (2662.1985 2300.2901) (2655.6489 2305.3435)
    ))
    ; P1754 -- see feature_dimensions_mm.csv
    ("05_STONE_JOINTS" 0 (
      (2753.4351 8931.2977) (3177.0992 8931.2977)
    ))
    ; P1755 -- see feature_dimensions_mm.csv
    ("05_STONE_JOINTS" 0 (
      (2753.4351 8824.4275) (2753.4351 8931.2977)
    ))
    ; P1756 -- see feature_dimensions_mm.csv
    ("05_STONE_JOINTS" 0 (
      (2753.4351 8824.4275) (3318.3206 8824.4275)
    ))
    ; P1757 -- see feature_dimensions_mm.csv
    ("05_STONE_JOINTS" 0 (
      (2753.4351 8717.5573) (2753.4351 8824.4275)
    ))
    ; P1758 -- see feature_dimensions_mm.csv
    ("05_STONE_JOINTS" 0 (
      (2753.4351 8717.5573) (3318.3206 8717.5573)
    ))
    ; P1759 -- see feature_dimensions_mm.csv
    ("05_STONE_JOINTS" 0 (
      (2807.2519 2122.5954) (2823.7405 2088.3817) (2834.6718 2061.0687) (3190.8397 2061.0687) (3127.2214 1984.7328)
    ))
    ; P1760 -- see feature_dimensions_mm.csv
    ("05_STONE_JOINTS" 0 (
      (2839.6947 9145.0382) (2866.4122 9145.0382)
    ))
    ; P1761 -- see feature_dimensions_mm.csv
    ("05_STONE_JOINTS" 0 (
      (2854.7481 1995.8321) (2857.4962 1984.7328) (2867.6794 1984.7328)
    ))
    ; P1762 -- see feature_dimensions_mm.csv
    ("05_STONE_JOINTS" 0 (
      (2867.6794 1984.7328) (2861.2061 1990.2748)
    ))
    ; P1763 -- see feature_dimensions_mm.csv
    ("05_STONE_JOINTS" 0 (
      (2866.4122 9358.7786) (3064.1221 9358.7786)
    ))
    ; P1764 -- see feature_dimensions_mm.csv
    ("05_STONE_JOINTS" 0 (
      (2866.4122 9145.0382) (2866.4122 9358.7786)
    ))
    ; P1765 -- see feature_dimensions_mm.csv
    ("05_STONE_JOINTS" 0 (
      (2866.4122 9145.0382) (3129.771 9145.0382)
    ))
    ; P1766 -- see feature_dimensions_mm.csv
    ("05_STONE_JOINTS" 0 (
      (2885.4962 1969.4656) (2867.6794 1984.7328)
    ))
    ; P1767 -- see feature_dimensions_mm.csv
    ("05_STONE_JOINTS" 0 (
      (3035.8779 8503.8168) (3318.3206 8503.8168)
    ))
    ; P1768 -- see feature_dimensions_mm.csv
    ("05_STONE_JOINTS" 0 (
      (3035.8779 8396.9466) (3035.8779 8503.8168)
    ))
    ; P1769 -- see feature_dimensions_mm.csv
    ("05_STONE_JOINTS" 0 (
      (3035.8779 8396.9466) (3459.542 8396.9466)
    ))
    ; P1770 -- see feature_dimensions_mm.csv
    ("05_STONE_JOINTS" 0 (
      (3035.8779 8290.0763) (3035.8779 8396.9466)
    ))
    ; P1771 -- see feature_dimensions_mm.csv
    ("05_STONE_JOINTS" 0 (
      (3035.8779 8290.0763) (3064.1221 8290.0763)
    ))
    ; P1772 -- see feature_dimensions_mm.csv
    ("05_STONE_JOINTS" 0 (
      (3629.0076 9572.5191) (3064.1221 9572.5191)
    ))
    ; P1773 -- see feature_dimensions_mm.csv
    ("05_STONE_JOINTS" 0 (
      (3064.1221 9358.7786) (3064.1221 9557.2519) (3064.1221 9572.5191)
    ))
    ; P1774 -- see feature_dimensions_mm.csv
    ("05_STONE_JOINTS" 0 (
      (3064.1221 9358.7786) (3572.5191 9358.7786)
    ))
    ; P1775 -- see feature_dimensions_mm.csv
    ("05_STONE_JOINTS" 0 (
      (3064.1221 8290.0763) (3459.542 8290.0763)
    ))
    ; P1776 -- see feature_dimensions_mm.csv
    ("05_STONE_JOINTS" 0 (
      (3064.1221 8076.3359) (3064.1221 8290.0763)
    ))
    ; P1777 -- see feature_dimensions_mm.csv
    ("05_STONE_JOINTS" 0 (
      (3127.2214 1984.7328) (3114.5038 1969.4656)
    ))
    ; P1778 -- see feature_dimensions_mm.csv
    ("05_STONE_JOINTS" 0 (
      (3269.3893 2233.1145) (3256.8244 2205.8015) (3246.0916 2177.7557) (3237.2366 2149.084) (3230.3206 2119.8931)
      (3225.3588 2090.3206) (3222.3664 2060.4885) (3221.374 2030.5344) (3221.374 1984.7328) (3127.2214 1984.7328)
    ))
    ; P1779 -- see feature_dimensions_mm.csv
    ("05_STONE_JOINTS" 0 (
      (3177.0992 8931.2977) (3177.0992 8946.5649) (3129.771 8946.5649) (3129.771 9145.0382)
    ))
    ; P1780 -- see feature_dimensions_mm.csv
    ("05_STONE_JOINTS" 0 (
      (3129.771 9145.0382) (3129.771 9312.9771) (3328.2443 9312.9771)
    ))
    ; P1781 -- see feature_dimensions_mm.csv
    ("05_STONE_JOINTS" 0 (
      (3129.771 931.2977) (3221.374 931.2977) (3221.374 1282.4427)
    ))
    ; P1782 -- see feature_dimensions_mm.csv
    ("05_STONE_JOINTS" 0 (
      (3177.0992 8931.2977) (3318.3206 8931.2977)
    ))
    ; P1783 -- see feature_dimensions_mm.csv
    ("05_STONE_JOINTS" 1 (
      (3221.374 1282.4427) (3129.771 1282.4427) (3129.771 1633.5878) (3221.374 1633.5878)
    ))
    ; P1784 -- see feature_dimensions_mm.csv
    ("05_STONE_JOINTS" 0 (
      (3314.6718 2305.3435) (3299.8473 2284.9924) (3283.7557 2259.542)
    ))
    ; P1785 -- see feature_dimensions_mm.csv
    ("05_STONE_JOINTS" 0 (
      (3454.1985 2427.1908) (3428.3206 2411.3588) (3403.5573 2393.9084) (3380.0 2374.8855) (3357.7557 2354.3969)
      (3336.9313 2332.5191) (3317.6031 2309.3588) (3314.6718 2305.3435)
    ))
    ; P1786 -- see feature_dimensions_mm.csv
    ("05_STONE_JOINTS" 0 (
      (3318.3206 8931.2977) (3741.9847 8931.2977)
    ))
    ; P1787 -- see feature_dimensions_mm.csv
    ("05_STONE_JOINTS" 0 (
      (3318.3206 8824.4275) (3318.3206 8931.2977)
    ))
    ; P1788 -- see feature_dimensions_mm.csv
    ("05_STONE_JOINTS" 0 (
      (3318.3206 8717.5573) (3318.3206 8824.4275)
    ))
    ; P1789 -- see feature_dimensions_mm.csv
    ("05_STONE_JOINTS" 0 (
      (3318.3206 8717.5573) (3629.0076 8717.5573)
    ))
    ; P1790 -- see feature_dimensions_mm.csv
    ("05_STONE_JOINTS" 0 (
      (3318.3206 8610.687) (3318.3206 8717.5573)
    ))
    ; P1791 -- see feature_dimensions_mm.csv
    ("05_STONE_JOINTS" 0 (
      (3318.3206 8503.8168) (3318.3206 8610.687)
    ))
    ; P1792 -- see feature_dimensions_mm.csv
    ("05_STONE_JOINTS" 0 (
      (3318.3206 8503.8168) (3459.542 8503.8168)
    ))
    ; P1793 -- see feature_dimensions_mm.csv
    ("05_STONE_JOINTS" 0 (
      (3328.2443 9145.0382) (3572.5191 9145.0382)
    ))
    ; P1794 -- see feature_dimensions_mm.csv
    ("05_STONE_JOINTS" 0 (
      (3459.542 8503.8168) (3629.0076 8503.8168)
    ))
    ; P1795 -- see feature_dimensions_mm.csv
    ("05_STONE_JOINTS" 0 (
      (3459.542 8396.9466) (3459.542 8503.8168)
    ))
    ; P1796 -- see feature_dimensions_mm.csv
    ("05_STONE_JOINTS" 0 (
      (3459.542 8396.9466) (4165.6489 8396.9466)
    ))
    ; P1797 -- see feature_dimensions_mm.csv
    ("05_STONE_JOINTS" 0 (
      (3459.542 8290.0763) (3459.542 8396.9466)
    ))
    ; P1798 -- see feature_dimensions_mm.csv
    ("05_STONE_JOINTS" 0 (
      (3459.542 8290.0763) (3629.0076 8290.0763)
    ))
    ; P1799 -- see feature_dimensions_mm.csv
    ("05_STONE_JOINTS" 0 (
      (3465.6489 2961.8321) (3633.5878 2961.8321)
    ))
    ; P1800 -- see feature_dimensions_mm.csv
    ("05_STONE_JOINTS" 0 (
      (3566.5038 2472.9466) (3537.3435 2464.2443) (3508.8244 2453.6794) (3481.0687 2441.313)
    ))
    ; P1801 -- see feature_dimensions_mm.csv
    ("05_STONE_JOINTS" 0 (
      (3574.3053 2474.7328) (3541.9847 2625.9542)
    ))
    ; P1802 -- see feature_dimensions_mm.csv
    ("05_STONE_JOINTS" 0 (
      (3572.5191 9358.7786) (3629.0076 9358.7786)
    ))
    ; P1803 -- see feature_dimensions_mm.csv
    ("05_STONE_JOINTS" 0 (
      (3572.5191 9251.9084) (3572.5191 9358.7786)
    ))
    ; P1804 -- see feature_dimensions_mm.csv
    ("05_STONE_JOINTS" 0 (
      (3572.5191 9251.9084) (3618.3206 9251.9084) (3618.3206 9312.9771) (3816.7939 9312.9771) (3816.7939 9251.9084)
    ))
    ; P1805 -- see feature_dimensions_mm.csv
    ("05_STONE_JOINTS" 0 (
      (3572.5191 9145.0382) (3572.5191 9251.9084)
    ))
    ; P1806 -- see feature_dimensions_mm.csv
    ("05_STONE_JOINTS" 0 (
      (3572.5191 9145.0382) (3618.3206 9145.0382)
    ))
    ; P1807 -- see feature_dimensions_mm.csv
    ("05_STONE_JOINTS" 0 (
      (4335.1145 9572.5191) (3629.0076 9572.5191)
    ))
    ; P1808 -- see feature_dimensions_mm.csv
    ("05_STONE_JOINTS" 0 (
      (3629.0076 9358.7786) (3629.0076 9557.2519) (3629.0076 9572.5191)
    ))
    ; P1809 -- see feature_dimensions_mm.csv
    ("05_STONE_JOINTS" 0 (
      (3629.0076 9358.7786) (4278.626 9358.7786)
    ))
    ; P1810 -- see feature_dimensions_mm.csv
    ("05_STONE_JOINTS" 0 (
      (3629.0076 8717.5573) (3939.6947 8717.5573)
    ))
    ; P1811 -- see feature_dimensions_mm.csv
    ("05_STONE_JOINTS" 0 (
      (3629.0076 8503.8168) (3629.0076 8717.5573)
    ))
    ; P1812 -- see feature_dimensions_mm.csv
    ("05_STONE_JOINTS" 0 (
      (3629.0076 8503.8168) (3939.6947 8503.8168)
    ))
    ; P1813 -- see feature_dimensions_mm.csv
    ("05_STONE_JOINTS" 0 (
      (3629.0076 8290.0763) (3939.6947 8290.0763)
    ))
    ; P1814 -- see feature_dimensions_mm.csv
    ("05_STONE_JOINTS" 0 (
      (3629.0076 8076.3359) (3629.0076 8290.0763)
    ))
    ; P1815 -- see feature_dimensions_mm.csv
    ("05_STONE_JOINTS" 0 (
      (3741.9847 8931.2977) (4024.4275 8931.2977)
    ))
    ; P1816 -- see feature_dimensions_mm.csv
    ("05_STONE_JOINTS" 0 (
      (3741.9847 8931.2977) (3741.9847 8946.5649) (3816.7939 8946.5649)
    ))
    ; P1817 -- see feature_dimensions_mm.csv
    ("05_STONE_JOINTS" 0 (
      (3755.7252 2961.8321) (3923.6641 2961.8321)
    ))
    ; P1818 -- see feature_dimensions_mm.csv
    ("05_STONE_JOINTS" 0 (
      (3816.7939 9251.9084) (4278.626 9251.9084)
    ))
    ; P1819 -- see feature_dimensions_mm.csv
    ("05_STONE_JOINTS" 0 (
      (3816.7939 9251.9084) (3816.7939 9145.0382) (4278.626 9145.0382)
    ))
    ; P1820 -- see feature_dimensions_mm.csv
    ("05_STONE_JOINTS" 0 (
      (3816.7939 9038.1679) (4306.8702 9038.1679)
    ))
    ; P1821 -- see feature_dimensions_mm.csv
    ("05_STONE_JOINTS" 0 (
      (4059.374 2305.3435) (4056.4427 2309.3588) (4037.1145 2332.5191) (4016.2901 2354.3969) (3994.0458 2374.8855)
      (3970.4885 2393.9084) (3945.7252 2411.3588) (3919.8473 2427.1908) (3892.9771 2441.313) (3865.2214 2453.6794)
      (3836.7023 2464.2443) (3807.542 2472.9466) (3799.7405 2474.7328) (3832.0611 2625.9542)
    ))
    ; P1822 -- see feature_dimensions_mm.csv
    ("05_STONE_JOINTS" 0 (
      (3939.6947 8717.5573) (4024.4275 8717.5573)
    ))
    ; P1823 -- see feature_dimensions_mm.csv
    ("05_STONE_JOINTS" 0 (
      (3939.6947 8503.8168) (3939.6947 8717.5573)
    ))
    ; P1824 -- see feature_dimensions_mm.csv
    ("05_STONE_JOINTS" 0 (
      (3939.6947 8503.8168) (4165.6489 8503.8168)
    ))
    ; P1825 -- see feature_dimensions_mm.csv
    ("05_STONE_JOINTS" 0 (
      (3939.6947 8290.0763) (4165.6489 8290.0763)
    ))
    ; P1826 -- see feature_dimensions_mm.csv
    ("05_STONE_JOINTS" 0 (
      (3939.6947 8076.3359) (3939.6947 8290.0763)
    ))
    ; P1827 -- see feature_dimensions_mm.csv
    ("05_STONE_JOINTS" 0 (
      (4024.4275 8931.2977) (4306.8702 8931.2977)
    ))
    ; P1828 -- see feature_dimensions_mm.csv
    ("05_STONE_JOINTS" 0 (
      (4024.4275 8717.5573) (4024.4275 8931.2977)
    ))
    ; P1829 -- see feature_dimensions_mm.csv
    ("05_STONE_JOINTS" 0 (
      (4024.4275 8717.5573) (4504.5802 8717.5573)
    ))
    ; P1830 -- see feature_dimensions_mm.csv
    ("05_STONE_JOINTS" 0 (
      (4045.8015 2961.8321) (4992.3664 2961.8321)
    ))
    ; P1831 -- see feature_dimensions_mm.csv
    ("05_STONE_JOINTS" 0 (
      (4059.374 2305.3435) (4992.3664 2305.3435)
    ))
    ; P1832 -- see feature_dimensions_mm.csv
    ("05_STONE_JOINTS" 0 (
      (4074.1985 2284.9924) (4059.374 2305.3435)
    ))
    ; P1833 -- see feature_dimensions_mm.csv
    ("05_STONE_JOINTS" 0 (
      (4152.6718 1984.7328) (4272.2595 1984.7328)
    ))
    ; P1834 -- see feature_dimensions_mm.csv
    ("05_STONE_JOINTS" 0 (
      (4152.6718 1633.5878) (4244.2748 1633.5878)
    ))
    ; P1835 -- see feature_dimensions_mm.csv
    ("05_STONE_JOINTS" 0 (
      (4152.6718 1282.4427) (4244.2748 1282.4427)
    ))
    ; P1836 -- see feature_dimensions_mm.csv
    ("05_STONE_JOINTS" 0 (
      (4152.6718 931.2977) (4244.2748 931.2977)
    ))
    ; P1837 -- see feature_dimensions_mm.csv
    ("05_STONE_JOINTS" 0 (
      (4165.6489 8503.8168) (4504.5802 8503.8168)
    ))
    ; P1838 -- see feature_dimensions_mm.csv
    ("05_STONE_JOINTS" 0 (
      (4165.6489 8396.9466) (4165.6489 8503.8168)
    ))
    ; P1839 -- see feature_dimensions_mm.csv
    ("05_STONE_JOINTS" 0 (
      (4165.6489 8290.0763) (4165.6489 8396.9466)
    ))
    ; P1840 -- see feature_dimensions_mm.csv
    ("05_STONE_JOINTS" 0 (
      (4165.6489 8290.0763) (4641.2214 8290.0763)
    ))
    ; P1841 -- see feature_dimensions_mm.csv
    ("05_STONE_JOINTS" 0 (
      (4272.2595 1984.7328) (4183.2061 2061.0687)
    ))
    ; P1842 -- see feature_dimensions_mm.csv
    ("05_STONE_JOINTS" 0 (
      (4290.0763 1969.4656) (4272.2595 1984.7328)
    ))
    ; P1843 -- see feature_dimensions_mm.csv
    ("05_STONE_JOINTS" 0 (
      (4278.626 9358.7786) (4335.1145 9358.7786)
    ))
    ; P1844 -- see feature_dimensions_mm.csv
    ("05_STONE_JOINTS" 0 (
      (4278.626 9251.9084) (4278.626 9358.7786)
    ))
    ; P1845 -- see feature_dimensions_mm.csv
    ("05_STONE_JOINTS" 0 (
      (4278.626 9145.0382) (4278.626 9251.9084)
    ))
    ; P1846 -- see feature_dimensions_mm.csv
    ("05_STONE_JOINTS" 0 (
      (4278.626 9145.0382) (4306.8702 9145.0382)
    ))
    ; P1847 -- see feature_dimensions_mm.csv
    ("05_STONE_JOINTS" 0 (
      (4306.8702 9145.0382) (4871.7557 9145.0382)
    ))
    ; P1848 -- see feature_dimensions_mm.csv
    ("05_STONE_JOINTS" 0 (
      (4306.8702 9038.1679) (4306.8702 9145.0382)
    ))
    ; P1849 -- see feature_dimensions_mm.csv
    ("05_STONE_JOINTS" 0 (
      (4306.8702 8931.2977) (4306.8702 9038.1679)
    ))
    ; P1850 -- see feature_dimensions_mm.csv
    ("05_STONE_JOINTS" 0 (
      (4306.8702 8931.2977) (4730.5344 8931.2977)
    ))
    ; P1851 -- see feature_dimensions_mm.csv
    ("05_STONE_JOINTS" 0 (
      (4900.0 9572.5191) (4335.1145 9572.5191)
    ))
    ; P1852 -- see feature_dimensions_mm.csv
    ("05_STONE_JOINTS" 0 (
      (4335.1145 9465.6489) (4335.1145 9557.2519) (4335.1145 9572.5191)
    ))
    ; P1853 -- see feature_dimensions_mm.csv
    ("05_STONE_JOINTS" 0 (
      (4335.1145 9465.6489) (4900.0 9465.6489)
    ))
    ; P1854 -- see feature_dimensions_mm.csv
    ("05_STONE_JOINTS" 0 (
      (4335.1145 9358.7786) (4335.1145 9465.6489)
    ))
    ; P1855 -- see feature_dimensions_mm.csv
    ("05_STONE_JOINTS" 0 (
      (4335.1145 9358.7786) (4900.0 9358.7786)
    ))
    ; P1856 -- see feature_dimensions_mm.csv
    ("05_STONE_JOINTS" 0 (
      (4504.5802 8717.5573) (4730.5344 8717.5573)
    ))
    ; P1857 -- see feature_dimensions_mm.csv
    ("05_STONE_JOINTS" 0 (
      (4504.5802 8610.687) (4504.5802 8717.5573)
    ))
    ; P1858 -- see feature_dimensions_mm.csv
    ("05_STONE_JOINTS" 0 (
      (4504.5802 8610.687) (4641.2214 8610.687)
    ))
    ; P1859 -- see feature_dimensions_mm.csv
    ("05_STONE_JOINTS" 0 (
      (4504.5802 8503.8168) (4504.5802 8610.687)
    ))
    ; P1860 -- see feature_dimensions_mm.csv
    ("05_STONE_JOINTS" 0 (
      (4504.5802 8503.8168) (4641.2214 8503.8168)
    ))
    ; P1861 -- see feature_dimensions_mm.csv
    ("05_STONE_JOINTS" 0 (
      (4519.084 1633.5878) (4992.3664 1633.5878)
    ))
    ; P1862 -- see feature_dimensions_mm.csv
    ("05_STONE_JOINTS" 0 (
      (4519.084 1282.4427) (4992.3664 1282.4427)
    ))
    ; P1863 -- see feature_dimensions_mm.csv
    ("05_STONE_JOINTS" 0 (
      (4595.4198 5969.4656) (4992.3664 5969.4656)
    ))
    ; P1864 -- see feature_dimensions_mm.csv
    ("05_STONE_JOINTS" 0 (
      (4595.4198 5465.6489) (4671.7557 5465.6489)
    ))
    ; P1865 -- see feature_dimensions_mm.csv
    ("05_STONE_JOINTS" 0 (
      (4641.2214 8290.0763) (4641.2214 8320.6107)
    ))
    ; P1866 -- see feature_dimensions_mm.csv
    ("05_STONE_JOINTS" 0 (
      (4641.2214 8122.1374) (4641.2214 8290.0763)
    ))
    ; P1867 -- see feature_dimensions_mm.csv
    ("05_STONE_JOINTS" 0 (
      (4669.2061 1984.7328) (4656.4885 1969.4656)
    ))
    ; P1868 -- see feature_dimensions_mm.csv
    ("05_STONE_JOINTS" 0 (
      (4669.2061 1984.7328) (4992.3664 1984.7328)
    ))
    ; P1869 -- see feature_dimensions_mm.csv
    ("05_STONE_JOINTS" 0 (
      (4732.8244 2061.0687) (4669.2061 1984.7328)
    ))
    ; P1870 -- see feature_dimensions_mm.csv
    ("05_STONE_JOINTS" 0 (
      (4691.6031 5465.6489) (4763.3588 5465.6489)
    ))
    ; P1871 -- see feature_dimensions_mm.csv
    ("05_STONE_JOINTS" 0 (
      (4730.5344 8931.2977) (4871.7557 8931.2977)
    ))
    ; P1872 -- see feature_dimensions_mm.csv
    ("05_STONE_JOINTS" 0 (
      (4730.5344 8717.5573) (4730.5344 8931.2977)
    ))
    ; P1873 -- see feature_dimensions_mm.csv
    ("05_STONE_JOINTS" 0 (
      (4730.5344 8717.5573) (4992.3664 8717.5573)
    ))
    ; P1874 -- see feature_dimensions_mm.csv
    ("05_STONE_JOINTS" 0 (
      (4860.0916 8641.2214) (4992.3664 8641.2214) (4992.3664 8717.5573)
    ))
    ; P1875 -- see feature_dimensions_mm.csv
    ("05_STONE_JOINTS" 0 (
      (4871.7557 9145.0382) (4984.7328 9145.0382)
    ))
    ; P1876 -- see feature_dimensions_mm.csv
    ("05_STONE_JOINTS" 0 (
      (4871.7557 8931.2977) (4871.7557 9145.0382)
    ))
    ; P1877 -- see feature_dimensions_mm.csv
    ("05_STONE_JOINTS" 0 (
      (4871.7557 8931.2977) (4992.3664 8931.2977)
    ))
    ; P1878 -- see feature_dimensions_mm.csv
    ("05_STONE_JOINTS" 0 (
      (4992.3664 9358.7786) (4992.3664 9557.2519) (4992.3664 9572.5191) (4900.0 9572.5191)
    ))
    ; P1879 -- see feature_dimensions_mm.csv
    ("05_STONE_JOINTS" 0 (
      (4900.0 9465.6489) (4900.0 9557.2519) (4900.0 9572.5191)
    ))
    ; P1880 -- see feature_dimensions_mm.csv
    ("05_STONE_JOINTS" 0 (
      (4900.0 9358.7786) (4900.0 9465.6489)
    ))
    ; P1881 -- see feature_dimensions_mm.csv
    ("05_STONE_JOINTS" 0 (
      (4900.0 9358.7786) (4984.7328 9358.7786)
    ))
    ; P1882 -- see feature_dimensions_mm.csv
    ("05_STONE_JOINTS" 0 (
      (4992.3664 8122.1374) (4977.0992 8122.1374) (4645.8015 8122.1374) (4645.8015 8076.3359) (4746.4275 8076.3359)
      (4932.6718 8076.3359) (4977.0992 8076.3359)
    ))
    ; P1883 -- see feature_dimensions_mm.csv
    ("05_STONE_JOINTS" 0 (
      (4984.7328 9358.7786) (4992.3664 9358.7786)
    ))
    ; P1884 -- see feature_dimensions_mm.csv
    ("05_STONE_JOINTS" 0 (
      (4984.7328 9251.9084) (4984.7328 9358.7786)
    ))
    ; P1885 -- see feature_dimensions_mm.csv
    ("05_STONE_JOINTS" 0 (
      (4984.7328 9251.9084) (4992.3664 9251.9084)
    ))
    ; P1886 -- see feature_dimensions_mm.csv
    ("05_STONE_JOINTS" 0 (
      (4984.7328 9145.0382) (4984.7328 9251.9084)
    ))
    ; P1887 -- see feature_dimensions_mm.csv
    ("05_STONE_JOINTS" 0 (
      (4984.7328 9145.0382) (4992.3664 9145.0382)
    ))
    ; P1888 -- see feature_dimensions_mm.csv
    ("05_STONE_JOINTS" 0 (
      (4992.3664 9251.9084) (4992.3664 9358.7786)
    ))
    ; P1889 -- see feature_dimensions_mm.csv
    ("05_STONE_JOINTS" 0 (
      (4992.3664 9145.0382) (4992.3664 9251.9084)
    ))
    ; P1890 -- see feature_dimensions_mm.csv
    ("05_STONE_JOINTS" 0 (
      (4992.3664 8931.2977) (4992.3664 9145.0382)
    ))
    ; P1891 -- see feature_dimensions_mm.csv
    ("05_STONE_JOINTS" 0 (
      (4992.3664 8717.5573) (4992.3664 8931.2977)
    ))
    ; P1892 -- see feature_dimensions_mm.csv
    ("05_STONE_JOINTS" 0 (
      (7022.9008 8122.1374) (4992.3664 8122.1374)
    ))
    ; P1893 -- see feature_dimensions_mm.csv
    ("05_STONE_JOINTS" 0 (
      (4992.3664 8122.1374) (4992.3664 8076.3359)
    ))
    ; P1894 -- see feature_dimensions_mm.csv
    ("05_STONE_JOINTS" 0 (
      (5160.3053 7679.3893) (5160.3053 7541.9847) (4992.3664 7541.9847)
    ))
    ; P1895 -- see feature_dimensions_mm.csv
    ("05_STONE_JOINTS" 0 (
      (4992.3664 7541.9847) (4992.3664 7526.7176)
    ))
    ; P1896 -- see feature_dimensions_mm.csv
    ("05_STONE_JOINTS" 0 (
      (4992.3664 7526.7176) (4992.3664 7374.0458) (4992.3664 7358.7786) (8671.7557 7358.7786)
    ))
    ; P1897 -- see feature_dimensions_mm.csv
    ("05_STONE_JOINTS" 0 (
      (4992.3664 6977.0992) (4992.3664 6961.8321)
    ))
    ; P1898 -- see feature_dimensions_mm.csv
    ("05_STONE_JOINTS" 0 (
      (4992.3664 5969.4656) (8671.7557 5969.4656)
    ))
    ; P1899 -- see feature_dimensions_mm.csv
    ("05_STONE_JOINTS" 0 (
      (4992.3664 5969.4656) (4992.3664 5816.7939)
    ))
    ; P1900 -- see feature_dimensions_mm.csv
    ("05_STONE_JOINTS" 0 (
      (8671.7557 6473.2824) (4992.3664 6473.2824) (4992.3664 5969.4656)
    ))
    ; P1901 -- see feature_dimensions_mm.csv
    ("05_STONE_JOINTS" 0 (
      (4992.3664 5465.6489) (4992.3664 5343.5115)
    ))
    ; P1902 -- see feature_dimensions_mm.csv
    ("05_STONE_JOINTS" 0 (
      (4992.3664 5343.5115) (5221.374 5343.5115)
    ))
    ; P1903 -- see feature_dimensions_mm.csv
    ("05_STONE_JOINTS" 0 (
      (4992.3664 5343.5115) (4992.3664 4717.5573) (5221.374 4717.5573)
    ))
    ; P1904 -- see feature_dimensions_mm.csv
    ("05_STONE_JOINTS" 0 (
      (5221.374 4091.6031) (4992.3664 4091.6031) (4992.3664 3740.458) (4992.3664 3679.3893) (4992.3664 3664.1221)
    ))
    ; P1905 -- see feature_dimensions_mm.csv
    ("05_STONE_JOINTS" 0 (
      (4992.3664 2839.6947) (5221.374 2839.6947)
    ))
    ; P1906 -- see feature_dimensions_mm.csv
    ("05_STONE_JOINTS" 0 (
      (4992.3664 1984.7328) (4992.3664 1633.5878)
    ))
    ; P1907 -- see feature_dimensions_mm.csv
    ("05_STONE_JOINTS" 0 (
      (4992.3664 1587.7863) (5221.374 1587.7863) (5221.374 2213.7405) (4992.3664 2213.7405) (4992.3664 1984.7328)
    ))
    ; P1908 -- see feature_dimensions_mm.csv
    ("05_STONE_JOINTS" 0 (
      (4992.3664 1633.5878) (4992.3664 1587.7863)
    ))
    ; P1909 -- see feature_dimensions_mm.csv
    ("05_STONE_JOINTS" 0 (
      (4992.3664 1587.7863) (4992.3664 1282.4427)
    ))
    ; P1910 -- see feature_dimensions_mm.csv
    ("05_STONE_JOINTS" 0 (
      (4992.3664 1282.4427) (4992.3664 961.8321)
    ))
    ; P1911 -- see feature_dimensions_mm.csv
    ("05_STONE_JOINTS" 0 (
      (4992.3664 961.8321) (5297.7099 961.8321) (6045.8015 961.8321) (6335.8779 961.8321) (7404.5802 961.8321)
      (7694.6565 961.8321)
    ))
    ; P1912 -- see feature_dimensions_mm.csv
    ("05_STONE_JOINTS" 0 (
      (4992.3664 961.8321) (4992.3664 931.2977)
    ))
    ; P1913 -- see feature_dimensions_mm.csv
    ("05_STONE_JOINTS" 1 (
      (4992.3664 931.2977) (4992.3664 793.8931) (4992.3664 656.4885) (4519.084 656.4885) (4519.084 931.2977)
    ))
    ; P1914 -- see feature_dimensions_mm.csv
    ("05_STONE_JOINTS" 0 (
      (5160.3053 7755.7252) (5160.3053 7740.458) (8671.7557 7740.458) (8671.7557 7755.7252)
    ))
    ; P1915 -- see feature_dimensions_mm.csv
    ("05_STONE_JOINTS" 0 (
      (5175.5725 3633.5878) (5175.5725 3465.6489) (5221.374 3465.6489) (5221.374 4091.6031)
    ))
    ; P1916 -- see feature_dimensions_mm.csv
    ("05_STONE_JOINTS" 0 (
      (5221.374 4717.5573) (5221.374 5343.5115)
    ))
    ; P1917 -- see feature_dimensions_mm.csv
    ("05_STONE_JOINTS" 0 (
      (5221.374 5343.5115) (5221.374 5358.7786) (5222.3359 5387.7405) (5225.2214 5416.5649) (5230.0305 5445.1603)
      (5236.7176 5473.374) (5245.2824 5501.0992) (5255.6641 5528.2137) (5267.8168 5554.5954) (5281.7099 5580.1527)
      (5297.2824 5604.7634) (5314.4427 5628.3053) (5333.145 5650.7023) (5353.2824 5671.8473) (5374.7939 5691.6489)
      (5397.5878 5710.0305) (5421.542 5726.916) (5446.5649 5742.2137) (5472.5496 5755.8626) (5499.4046 5767.8321)
      (5526.9924 5778.0305) (5555.1908 5786.4427) (5583.8931 5793.0229) (5612.9618 5797.7405) (5642.3053 5800.5802)
      (5671.7557 5801.5267) (5701.2061 5800.5802) (5730.5496 5797.7405) (5759.6183 5793.0229) (5788.3206 5786.4427)
      (5816.5191 5778.0305) (5844.1069 5767.8321) (5870.9618 5755.8626) (5896.9466 5742.2137) (5921.9695 5726.916)
      (5945.9237 5710.0305) (5968.7176 5691.6489) (5990.229 5671.8473) (6010.3664 5650.7023) (6029.0687 5628.3053)
      (6046.229 5604.7634) (6061.8015 5580.1527) (6075.6947 5554.5954) (6087.8473 5528.2137) (6098.229 5501.0992)
      (6106.7939 5473.374) (6113.4809 5445.1603) (6118.2901 5416.5649) (6121.1756 5387.7405) (6122.1374 5358.7786)
      (6122.1374 5343.5115)
    ))
    ; P1918 -- see feature_dimensions_mm.csv
    ("05_STONE_JOINTS" 0 (
      (5221.374 4091.6031) (5221.374 4717.5573)
    ))
    ; P1919 -- see feature_dimensions_mm.csv
    ("05_STONE_JOINTS" 0 (
      (6122.1374 5343.5115) (6259.542 5343.5115)
    ))
    ; P1920 -- see feature_dimensions_mm.csv
    ("05_STONE_JOINTS" 0 (
      (6122.1374 5343.5115) (6122.1374 4717.5573)
    ))
    ; P1921 -- see feature_dimensions_mm.csv
    ("05_STONE_JOINTS" 0 (
      (6122.1374 4717.5573) (6259.542 4717.5573)
    ))
    ; P1922 -- see feature_dimensions_mm.csv
    ("05_STONE_JOINTS" 0 (
      (6122.1374 4717.5573) (6122.1374 4091.6031)
    ))
    ; P1923 -- see feature_dimensions_mm.csv
    ("05_STONE_JOINTS" 0 (
      (6122.1374 4091.6031) (6259.542 4091.6031)
    ))
    ; P1924 -- see feature_dimensions_mm.csv
    ("05_STONE_JOINTS" 0 (
      (6122.1374 4091.6031) (6122.1374 3465.6489) (6259.542 3465.6489) (6259.542 4091.6031)
    ))
    ; P1925 -- see feature_dimensions_mm.csv
    ("05_STONE_JOINTS" 0 (
      (6122.1374 2839.6947) (6259.542 2839.6947)
    ))
    ; P1926 -- see feature_dimensions_mm.csv
    ("05_STONE_JOINTS" 0 (
      (6122.1374 2213.7405) (6259.542 2213.7405)
    ))
    ; P1927 -- see feature_dimensions_mm.csv
    ("05_STONE_JOINTS" 0 (
      (6122.1374 1587.7863) (6259.542 1587.7863)
    ))
    ; P1928 -- see feature_dimensions_mm.csv
    ("05_STONE_JOINTS" 0 (
      (6259.542 4717.5573) (6259.542 5343.5115)
    ))
    ; P1929 -- see feature_dimensions_mm.csv
    ("05_STONE_JOINTS" 0 (
      (6259.542 5343.5115) (6259.542 5358.7786) (6260.855 5387.7405) (6264.7634 5416.5649) (6271.2824 5445.1603)
      (6280.3511 5473.374) (6291.9542 5501.0992) (6306.0305 5528.2137) (6322.5191 5554.5954) (6341.3588 5580.1527)
      (6362.458 5604.7634) (6385.7405 5628.3053) (6411.084 5650.7023) (6438.4122 5671.8473) (6467.5725 5691.6489)
      (6498.4733 5710.0305) (6530.9466 5726.916) (6564.8855 5742.2137) (6600.1221 5755.8626) (6636.5344 5767.8321)
      (6673.9237 5778.0305) (6712.1679 5786.4427) (6751.084 5793.0229) (6790.5191 5797.7405) (6830.2901 5800.5802)
      (6870.229 5801.5267) (6910.1679 5800.5802) (6949.9389 5797.7405) (6989.374 5793.0229) (7028.2901 5786.4427)
      (7066.5344 5778.0305) (7103.9237 5767.8321) (7140.3359 5755.8626) (7175.5725 5742.2137) (7209.5115 5726.916)
      (7241.9847 5710.0305) (7272.8855 5691.6489) (7302.0458 5671.8473) (7329.374 5650.7023) (7354.7176 5628.3053)
      (7378.0 5604.7634) (7399.0992 5580.1527) (7417.9389 5554.5954) (7434.4275 5528.2137) (7448.5038 5501.0992)
      (7460.1069 5473.374) (7469.1756 5445.1603) (7475.6947 5416.5649) (7479.6031 5387.7405) (7480.916 5358.7786)
      (7480.916 5343.5115)
    ))
    ; P1930 -- see feature_dimensions_mm.csv
    ("05_STONE_JOINTS" 0 (
      (6259.542 4091.6031) (6259.542 4717.5573)
    ))
    ; P1931 -- see feature_dimensions_mm.csv
    ("05_STONE_JOINTS" 0 (
      (8671.7557 8122.1374) (7039.6947 8122.1374)
    ))
    ; P1932 -- see feature_dimensions_mm.csv
    ("05_STONE_JOINTS" 0 (
      (7480.916 5343.5115) (7618.3206 5343.5115)
    ))
    ; P1933 -- see feature_dimensions_mm.csv
    ("05_STONE_JOINTS" 0 (
      (7480.916 5343.5115) (7480.916 4717.5573)
    ))
    ; P1934 -- see feature_dimensions_mm.csv
    ("05_STONE_JOINTS" 0 (
      (7480.916 4717.5573) (7618.3206 4717.5573)
    ))
    ; P1935 -- see feature_dimensions_mm.csv
    ("05_STONE_JOINTS" 0 (
      (7480.916 4717.5573) (7480.916 4091.6031)
    ))
    ; P1936 -- see feature_dimensions_mm.csv
    ("05_STONE_JOINTS" 0 (
      (7480.916 4091.6031) (7618.3206 4091.6031)
    ))
    ; P1937 -- see feature_dimensions_mm.csv
    ("05_STONE_JOINTS" 0 (
      (7480.916 4091.6031) (7480.916 3465.6489) (7618.3206 3465.6489) (7618.3206 4091.6031)
    ))
    ; P1938 -- see feature_dimensions_mm.csv
    ("05_STONE_JOINTS" 0 (
      (7480.916 2839.6947) (7618.3206 2839.6947)
    ))
    ; P1939 -- see feature_dimensions_mm.csv
    ("05_STONE_JOINTS" 0 (
      (7618.3206 4717.5573) (7618.3206 5343.5115)
    ))
    ; P1940 -- see feature_dimensions_mm.csv
    ("05_STONE_JOINTS" 0 (
      (7618.3206 5343.5115) (7618.3206 5358.7786) (7619.2824 5387.7405) (7622.1679 5416.5649) (7626.9771 5445.1603)
      (7633.6641 5473.374) (7642.229 5501.0992) (7652.6107 5528.2137) (7664.7634 5554.5954)
    ))
    ; P1941 -- see feature_dimensions_mm.csv
    ("05_STONE_JOINTS" 0 (
      (7618.3206 4091.6031) (7618.3206 4717.5573)
    ))
    ; P1942 -- see feature_dimensions_mm.csv
    ("05_STONE_JOINTS" 0 (
      (7618.3206 2213.7405) (7480.916 2213.7405) (7480.916 1587.7863) (7618.3206 1587.7863)
    ))
    ; P1943 -- see feature_dimensions_mm.csv
    ("05_STONE_JOINTS" 0 (
      (7678.6565 5580.1527) (7694.229 5604.7634) (7711.3893 5628.3053)
    ))
    ; P1944 -- see feature_dimensions_mm.csv
    ("05_STONE_JOINTS" 0 (
      (7730.0916 5650.7023) (7750.229 5671.8473)
    ))
    ; P1945 -- see feature_dimensions_mm.csv
    ("05_STONE_JOINTS" 0 (
      (7771.7405 5691.6489) (7794.5344 5710.0305) (7818.4885 5726.916) (7843.5115 5742.2137) (7869.4962 5755.8626)
      (7896.3511 5767.8321) (7923.9389 5778.0305) (7952.1374 5786.4427)
    ))
    ; P1946 -- see feature_dimensions_mm.csv
    ("05_STONE_JOINTS" 0 (
      (7980.8397 5793.0229) (8009.9084 5797.7405) (8039.2519 5800.5802) (8068.7023 5801.5267) (8098.1527 5800.5802)
    ))
    ; P1947 -- see feature_dimensions_mm.csv
    ("05_STONE_JOINTS" 0 (
      (8127.4962 5797.7405) (8156.5649 5793.0229) (8185.2672 5786.4427) (8213.4656 5778.0305) (8241.0534 5767.8321)
      (8267.9084 5755.8626) (8293.8931 5742.2137) (8318.916 5726.916) (8342.8702 5710.0305) (8365.6641 5691.6489)
      (8387.1756 5671.8473) (8407.313 5650.7023) (8426.0153 5628.3053)
    ))
    ; P1948 -- see feature_dimensions_mm.csv
    ("05_STONE_JOINTS" 0 (
      (8442.7481 961.8321) (8473.2824 961.8321)
    ))
    ; P1949 -- see feature_dimensions_mm.csv
    ("05_STONE_JOINTS" 0 (
      (8443.1756 5604.7634) (8458.7481 5580.1527) (8472.6412 5554.5954) (8484.7939 5528.2137) (8495.1756 5501.0992)
      (8503.7405 5473.374) (8510.4275 5445.1603) (8515.2366 5416.5649) (8518.1221 5387.7405)
    ))
    ; P1950 -- see feature_dimensions_mm.csv
    ("05_STONE_JOINTS" 0 (
      (8519.084 5358.7786) (8519.084 5343.5115)
    ))
    ; P1951 -- see feature_dimensions_mm.csv
    ("05_STONE_JOINTS" 0 (
      (8519.084 5343.5115) (8671.7557 5343.5115)
    ))
    ; P1952 -- see feature_dimensions_mm.csv
    ("05_STONE_JOINTS" 0 (
      (8519.084 5343.5115) (8519.084 4717.5573)
    ))
    ; P1953 -- see feature_dimensions_mm.csv
    ("05_STONE_JOINTS" 0 (
      (8519.084 4091.6031) (8671.7557 4091.6031) (8671.7557 4717.5573) (8519.084 4717.5573)
    ))
    ; P1954 -- see feature_dimensions_mm.csv
    ("05_STONE_JOINTS" 0 (
      (8519.084 4717.5573) (8519.084 4091.6031)
    ))
    ; P1955 -- see feature_dimensions_mm.csv
    ("05_STONE_JOINTS" 0 (
      (8519.084 4091.6031) (8519.084 3618.3206) (8671.7557 3618.3206)
    ))
    ; P1956 -- see feature_dimensions_mm.csv
    ("05_STONE_JOINTS" 0 (
      (8671.7557 7374.0458) (8671.7557 7679.3893)
    ))
    ; P1957 -- see feature_dimensions_mm.csv
    ("05_STONE_JOINTS" 0 (
      (10290.0763 6992.3664) (13832.0611 6992.3664)
    ))
    ; P1958 -- see feature_dimensions_mm.csv
    ("05_STONE_JOINTS" 0 (
      (10290.0763 6564.8855) (13832.0611 6564.8855) (13832.0611 6656.4885) (13832.0611 6977.0992) (13832.0611 6992.3664)
    ))
    ; P1959 -- see feature_dimensions_mm.csv
    ("05_STONE_JOINTS" 0 (
      (10290.0763 5969.4656) (10687.0229 5969.4656)
    ))
    ; P1960 -- see feature_dimensions_mm.csv
    ("05_STONE_JOINTS" 0 (
      (10290.0763 5465.6489) (10366.4122 5465.6489) (10386.2595 5465.6489) (10458.0153 5465.6489) (10477.8626 5465.6489)
      (10549.6183 5465.6489) (10569.4656 5465.6489) (10641.2214 5465.6489) (10661.0687 5465.6489) (10687.0229 5465.6489)
      (10687.0229 5816.7939)
    ))
    ; P1961 -- see feature_dimensions_mm.csv
    ("05_STONE_JOINTS" 0 (
      (13832.0611 2961.8321) (13832.0611 3267.1756) (10519.084 3267.1756)
    ))
    ; P1962 -- see feature_dimensions_mm.csv
    ("05_STONE_JOINTS" 0 (
      (10519.084 2961.8321) (11038.1679 2961.8321)
    ))
    ; P1963 -- see feature_dimensions_mm.csv
    ("05_STONE_JOINTS" 0 (
      (10519.084 2641.2214) (13832.0611 2641.2214)
    ))
    ; P1964 -- see feature_dimensions_mm.csv
    ("05_STONE_JOINTS" 0 (
      (10519.084 2008.7176) (10547.0687 1984.7328)
    ))
    ; P1965 -- see feature_dimensions_mm.csv
    ("05_STONE_JOINTS" 0 (
      (10519.084 1984.7328) (10547.0687 1984.7328)
    ))
    ; P1966 -- see feature_dimensions_mm.csv
    ("05_STONE_JOINTS" 0 (
      (10519.084 1633.5878) (10580.1527 1633.5878)
    ))
    ; P1967 -- see feature_dimensions_mm.csv
    ("05_STONE_JOINTS" 0 (
      (10519.084 1282.4427) (10580.1527 1282.4427) (10580.1527 1633.5878)
    ))
    ; P1968 -- see feature_dimensions_mm.csv
    ("05_STONE_JOINTS" 0 (
      (10519.084 931.2977) (10580.1527 931.2977)
    ))
    ; P1969 -- see feature_dimensions_mm.csv
    ("05_STONE_JOINTS" 0 (
      (10547.0687 1984.7328) (10564.8855 1969.4656)
    ))
    ; P1970 -- see feature_dimensions_mm.csv
    ("05_STONE_JOINTS" 0 (
      (10610.687 1862.5954) (10580.1527 1862.5954) (10580.1527 1633.5878)
    ))
    ; P1971 -- see feature_dimensions_mm.csv
    ("05_STONE_JOINTS" 0 (
      (10811.0687 2122.5954) (10794.5802 2088.3817) (10783.6489 2061.0687) (10519.084 2061.0687) (10519.084 2305.3435)
      (10962.6718 2305.3435)
    ))
    ; P1972 -- see feature_dimensions_mm.csv
    ("05_STONE_JOINTS" 0 (
      (10962.6718 2305.3435) (10956.1221 2300.2901) (10926.9618 2274.6107) (10899.6336 2247.1908) (10874.2901 2218.1527)
      (10851.0076 2187.6183) (10829.9084 2155.7252)
    ))
    ; P1973 -- see feature_dimensions_mm.csv
    ("05_STONE_JOINTS" 0 (
      (10987.0229 2324.1221) (10962.6718 2305.3435)
    ))
    ; P1974 -- see feature_dimensions_mm.csv
    ("05_STONE_JOINTS" 0 (
      (11160.3053 2961.8321) (11160.3053 2809.1603) (11038.1679 2809.1603) (11038.1679 2961.8321)
    ))
    ; P1975 -- see feature_dimensions_mm.csv
    ("05_STONE_JOINTS" 0 (
      (11038.1679 2961.8321) (11038.1679 3099.2366) (11160.3053 3099.2366) (11160.3053 2961.8321)
    ))
    ; P1976 -- see feature_dimensions_mm.csv
    ("05_STONE_JOINTS" 0 (
      (11160.3053 2961.8321) (11312.9771 2961.8321)
    ))
    ; P1977 -- see feature_dimensions_mm.csv
    ("05_STONE_JOINTS" 0 (
      (11435.1145 2961.8321) (11435.1145 2809.1603) (11312.9771 2809.1603) (11312.9771 2961.8321)
    ))
    ; P1978 -- see feature_dimensions_mm.csv
    ("05_STONE_JOINTS" 0 (
      (11312.9771 2961.8321) (11312.9771 3099.2366) (11435.1145 3099.2366) (11435.1145 2961.8321)
    ))
    ; P1979 -- see feature_dimensions_mm.csv
    ("05_STONE_JOINTS" 0 (
      (11435.1145 2961.8321) (11603.0534 2961.8321)
    ))
    ; P1980 -- see feature_dimensions_mm.csv
    ("05_STONE_JOINTS" 0 (
      (11725.1908 2961.8321) (11725.1908 2809.1603) (11603.0534 2809.1603) (11603.0534 2961.8321)
    ))
    ; P1981 -- see feature_dimensions_mm.csv
    ("05_STONE_JOINTS" 0 (
      (11603.0534 2961.8321) (11603.0534 3099.2366) (11725.1908 3099.2366) (11725.1908 2961.8321)
    ))
    ; P1982 -- see feature_dimensions_mm.csv
    ("05_STONE_JOINTS" 0 (
      (11725.1908 2961.8321) (12412.2137 2961.8321)
    ))
    ; P1983 -- see feature_dimensions_mm.csv
    ("05_STONE_JOINTS" 0 (
      (11754.8855 2305.3435) (11730.5344 2324.1221)
    ))
    ; P1984 -- see feature_dimensions_mm.csv
    ("05_STONE_JOINTS" 0 (
      (11754.8855 2305.3435) (12306.1832 2305.3435)
    ))
    ; P1985 -- see feature_dimensions_mm.csv
    ("05_STONE_JOINTS" 0 (
      (12127.1603 2061.0687) (11933.9084 2061.0687) (11922.9771 2088.3817) (11906.4885 2122.5954) (11887.6489 2155.7252)
      (11866.5496 2187.6183) (11843.2672 2218.1527) (11817.9237 2247.1908) (11790.5954 2274.6107) (11761.4351 2300.2901)
      (11754.8855 2305.3435)
    ))
    ; P1986 -- see feature_dimensions_mm.csv
    ("05_STONE_JOINTS" 0 (
      (12306.1832 2305.3435) (12299.6336 2300.2901)
    ))
    ; P1987 -- see feature_dimensions_mm.csv
    ("05_STONE_JOINTS" 0 (
      (12330.5344 2324.1221) (12306.1832 2305.3435)
    ))
    ; P1988 -- see feature_dimensions_mm.csv
    ("05_STONE_JOINTS" 0 (
      (12396.9466 2365.8473) (12363.0076 2346.0)
    ))
    ; P1989 -- see feature_dimensions_mm.csv
    ("05_STONE_JOINTS" 0 (
      (12592.9466 2433.2366) (12583.145 2431.7252) (12544.229 2423.1908) (12505.9847 2412.2901) (12468.5954 2399.0534)
      (12432.1832 2383.542)
    ))
    ; P1990 -- see feature_dimensions_mm.csv
    ("05_STONE_JOINTS" 0 (
      (12534.3511 2961.8321) (12702.2901 2961.8321)
    ))
    ; P1991 -- see feature_dimensions_mm.csv
    ("05_STONE_JOINTS" 0 (
      (12821.4351 2431.7252) (12811.6336 2433.2366)
    ))
    ; P1992 -- see feature_dimensions_mm.csv
    ("05_STONE_JOINTS" 0 (
      (12824.4275 2961.8321) (12992.3664 2961.8321)
    ))
    ; P1993 -- see feature_dimensions_mm.csv
    ("05_STONE_JOINTS" 0 (
      (13007.6336 2365.8473) (12972.3969 2383.542) (12935.9847 2399.0534) (12898.5954 2412.2901) (12860.3511 2423.1908)
    ))
    ; P1994 -- see feature_dimensions_mm.csv
    ("05_STONE_JOINTS" 0 (
      (13098.3969 2305.3435) (13074.0458 2324.1221) (13041.5725 2346.0)
    ))
    ; P1995 -- see feature_dimensions_mm.csv
    ("05_STONE_JOINTS" 0 (
      (13098.3969 2305.3435) (13832.0611 2305.3435)
    ))
    ; P1996 -- see feature_dimensions_mm.csv
    ("05_STONE_JOINTS" 0 (
      (13737.9084 1984.7328) (13801.5267 2061.0687) (13277.4198 2061.0687) (13266.4885 2088.3817) (13250.0 2122.5954)
      (13231.1603 2155.7252) (13210.0611 2187.6183) (13186.7786 2218.1527) (13161.4351 2247.1908) (13134.1069 2274.6107)
      (13104.9466 2300.2901) (13098.3969 2305.3435)
    ))
    ; P1997 -- see feature_dimensions_mm.csv
    ("05_STONE_JOINTS" 0 (
      (13114.5038 2961.8321) (13832.0611 2961.8321)
    ))
    ; P1998 -- see feature_dimensions_mm.csv
    ("05_STONE_JOINTS" 0 (
      (13325.6947 1984.7328) (13293.3588 2012.4427)
    ))
    ; P1999 -- see feature_dimensions_mm.csv
    ("05_STONE_JOINTS" 0 (
      (13300.2443 1984.7328) (13325.6947 1984.7328)
    ))
    ; P2000 -- see feature_dimensions_mm.csv
    ("05_STONE_JOINTS" 0 (
      (13343.5115 1969.4656) (13325.6947 1984.7328)
    ))
    ; P2001 -- see feature_dimensions_mm.csv
    ("05_STONE_JOINTS" 0 (
      (13435.1145 5969.4656) (13832.0611 5969.4656)
    ))
    ; P2002 -- see feature_dimensions_mm.csv
    ("05_STONE_JOINTS" 0 (
      (13737.9084 1984.7328) (13725.1908 1969.4656) (13725.1908 1862.5954) (13557.2519 1862.5954)
    ))
    ; P2003 -- see feature_dimensions_mm.csv
    ("05_STONE_JOINTS" 0 (
      (13557.2519 1633.5878) (13832.0611 1633.5878)
    ))
    ; P2004 -- see feature_dimensions_mm.csv
    ("05_STONE_JOINTS" 0 (
      (13557.2519 1282.4427) (13832.0611 1282.4427)
    ))
    ; P2005 -- see feature_dimensions_mm.csv
    ("05_STONE_JOINTS" 0 (
      (13557.2519 931.2977) (13832.0611 931.2977)
    ))
    ; P2006 -- see feature_dimensions_mm.csv
    ("05_STONE_JOINTS" 0 (
      (13557.2519 656.4885) (13832.0611 656.4885) (13832.0611 931.2977)
    ))
    ; P2007 -- see feature_dimensions_mm.csv
    ("05_STONE_JOINTS" 0 (
      (13737.9084 1984.7328) (13832.0611 1984.7328)
    ))
    ; P2008 -- see feature_dimensions_mm.csv
    ("05_STONE_JOINTS" 0 (
      (13832.0611 6992.3664) (13832.0611 7526.7176)
    ))
    ; P2009 -- see feature_dimensions_mm.csv
    ("05_STONE_JOINTS" 1 (
      (13832.0611 7526.7176) (13832.0611 7541.9847) (10290.0763 7541.9847) (10290.0763 7526.7176)
    ))
    ; P2010 -- see feature_dimensions_mm.csv
    ("05_STONE_JOINTS" 0 (
      (13832.0611 2641.2214) (13832.0611 2961.8321)
    ))
    ; P2011 -- see feature_dimensions_mm.csv
    ("05_STONE_JOINTS" 0 (
      (13832.0611 2305.3435) (13832.0611 2641.2214)
    ))
    ; P2012 -- see feature_dimensions_mm.csv
    ("05_STONE_JOINTS" 0 (
      (13832.0611 1984.7328) (13832.0611 2305.3435)
    ))
    ; P2013 -- see feature_dimensions_mm.csv
    ("05_STONE_JOINTS" 0 (
      (13832.0611 1633.5878) (13832.0611 1984.7328)
    ))
    ; P2014 -- see feature_dimensions_mm.csv
    ("05_STONE_JOINTS" 0 (
      (13832.0611 1282.4427) (13832.0611 1633.5878)
    ))
    ; P2015 -- see feature_dimensions_mm.csv
    ("05_STONE_JOINTS" 0 (
      (13832.0611 931.2977) (13832.0611 1282.4427)
    ))
    ; P2016 -- see feature_dimensions_mm.csv
    ("06_ORNAMENT" 0 (
      (4351.145 6244.2748) (1603.0534 6244.2748) (1603.0534 6015.2672) (1358.7786 6015.2672) (1358.7786 5969.4656)
    ))
    ; P2017 -- see feature_dimensions_mm.csv
    ("06_ORNAMENT" 0 (
      (1358.7786 3740.458) (1358.7786 3679.3893) (1358.7786 3664.1221)
    ))
    ; P2018 -- see feature_dimensions_mm.csv
    ("06_ORNAMENT" 0 (
      (1801.5267 1609.5878) (1808.3206 1607.9084) (1819.6489 1606.1221) (1831.4198 1605.2214) (1843.4504 1605.2366)
      (1855.5878 1606.2443) (1867.6183 1608.2443) (1879.4046 1611.2824) (1890.7634 1615.4046) (1901.5267 1620.6412)
      (1911.5115 1627.0382) (1920.5496 1634.626) (1928.4733 1643.4351) (1935.1145 1653.5267) (1923.7099 1658.7786)
      (1911.8931 1662.3053) (1899.771 1664.229) (1887.5115 1664.6565) (1875.2519 1663.7252) (1863.1145 1661.5573)
      (1851.2519 1658.2595) (1839.8015 1653.9695) (1828.916 1648.7939) (1818.7023 1642.8702) (1809.3435 1636.3053)
      (1801.5267 1629.7099)
    ))
    ; P2019 -- see feature_dimensions_mm.csv
    ("06_ORNAMENT" 0 (
      (2015.2672 2839.6947) (2000.0 2854.9618) (1984.7328 2839.6947)
    ))
    ; P2020 -- see feature_dimensions_mm.csv
    ("06_ORNAMENT" 0 (
      (2259.542 4412.2137) (2229.0076 4412.2137) (2152.6718 4412.2137) (2045.8015 4412.2137) (2030.5344 4412.2137)
    ))
    ; P2021 -- see feature_dimensions_mm.csv
    ("06_ORNAMENT" 0 (
      (2305.3435 2839.6947) (2290.0763 2854.9618) (2274.8092 2839.6947)
    ))
    ; P2022 -- see feature_dimensions_mm.csv
    ("06_ORNAMENT" 0 (
      (2432.0 4473.2824) (2433.5878 4475.0687) (2415.2672 4495.6794) (2396.9466 4475.0687) (2398.5344 4473.2824)
    ))
    ; P2023 -- see feature_dimensions_mm.csv
    ("06_ORNAMENT" 0 (
      (2415.7099 3832.0611) (2433.5878 3852.1679) (2415.2672 3872.7786) (2396.9466 3852.1679) (2414.8244 3832.0611)
    ))
    ; P2024 -- see feature_dimensions_mm.csv
    ("06_ORNAMENT" 0 (
      (2587.7252 4473.2824) (2589.313 4475.0687) (2570.9924 4495.6794) (2552.6718 4475.0687) (2554.2595 4473.2824)
    ))
    ; P2025 -- see feature_dimensions_mm.csv
    ("06_ORNAMENT" 0 (
      (2595.4198 2839.6947) (2580.1527 2854.9618) (2564.8855 2839.6947)
    ))
    ; P2026 -- see feature_dimensions_mm.csv
    ("06_ORNAMENT" 0 (
      (2571.4351 3832.0611) (2589.313 3852.1679) (2570.9924 3872.7786) (2552.6718 3852.1679) (2570.5496 3832.0611)
    ))
    ; P2027 -- see feature_dimensions_mm.csv
    ("06_ORNAMENT" 0 (
      (2603.4504 5482.7481) (2605.5573 5481.5878) (2611.8626 5479.9237) (2618.1832 5479.0534) (2622.916 5478.4733)
      (2625.0229 5477.4046) (2624.2901 5475.1603) (2621.3588 5471.4046) (2617.4962 5466.3359) (2614.2137 5460.7023)
      (2612.7481 5455.6183) (2613.771 5452.1985) (2617.1908 5451.1756) (2622.2748 5452.6412) (2627.9084 5455.9237)
      (2632.9771 5459.771) (2636.7328 5462.7023) (2638.9771 5463.4351) (2640.0458 5461.3435) (2640.6412 5456.6107)
      (2641.4962 5450.2901) (2643.1603 5443.9847) (2645.7099 5439.3588) (2648.855 5437.6641) (2652.0 5439.3588)
      (2654.5496 5443.9847) (2656.2137 5450.2901) (2657.0687 5456.6107) (2657.6641 5461.3435) (2658.7328 5463.4351)
      (2660.9771 5462.7023) (2664.7328 5459.771) (2669.8015 5455.9237) (2675.4351 5452.6412) (2680.5191 5451.1756)
      (2683.9389 5452.1985) (2684.9618 5455.6183) (2683.4962 5460.7023) (2680.2137 5466.3359) (2676.3511 5471.4046)
      (2673.4198 5475.1603) (2672.687 5477.4046) (2674.7939 5478.4733) (2679.5267 5479.0534) (2685.8473 5479.9237)
      (2692.1527 5481.5878) (2696.7786 5484.1374) (2698.4733 5487.2824) (2696.7786 5490.4275) (2692.1527 5492.9771)
      (2685.8473 5494.6412) (2679.5267 5495.4962) (2674.7939 5496.0916) (2672.687 5497.1603) (2673.4198 5499.4046)
      (2676.3511 5503.1603) (2679.0687 5506.7176)
    ))
    ; P2028 -- see feature_dimensions_mm.csv
    ("06_ORNAMENT" 0 (
      (2639.7863 5494.7176) (2621.7252 5489.0229)
    ))
    ; P2029 -- see feature_dimensions_mm.csv
    ("06_ORNAMENT" 0 (
      (2639.7863 5494.7176) (2637.8473 5491.8321) (2636.9466 5487.2824) (2637.8473 5482.7176) (2640.4275 5478.855)
      (2644.3053 5476.2748) (2648.855 5475.374) (2653.4046 5476.2748) (2657.2824 5478.855) (2659.8626 5482.7176)
      (2660.7634 5487.2824) (2659.8626 5491.8321) (2657.2824 5495.6947) (2653.4046 5498.2748) (2651.9542 5498.5649)
    ))
    ; P2030 -- see feature_dimensions_mm.csv
    ("06_ORNAMENT" 0 (
      (2651.9542 5498.5649) (2639.7863 5494.7176)
    ))
    ; P2031 -- see feature_dimensions_mm.csv
    ("06_ORNAMENT" 0 (
      (2661.771 5501.6641) (2651.9542 5498.5649)
    ))
    ; P2032 -- see feature_dimensions_mm.csv
    ("06_ORNAMENT" 0 (
      (2743.4504 4473.2824) (2745.0382 4475.0687) (2726.7176 4495.6794) (2708.3969 4475.0687) (2709.9847 4473.2824)
    ))
    ; P2033 -- see feature_dimensions_mm.csv
    ("06_ORNAMENT" 0 (
      (2727.1603 3832.0611) (2745.0382 3852.1679) (2726.7176 3872.7786) (2708.3969 3852.1679) (2726.2748 3832.0611)
    ))
    ; P2034 -- see feature_dimensions_mm.csv
    ("06_ORNAMENT" 0 (
      (2855.6183 4412.2137) (2857.8779 4409.3282) (2858.6107 4407.084) (2856.5038 4406.0153) (2851.771 4405.4198)
      (2845.4504 4404.5649) (2839.145 4402.9008) (2834.5191 4400.3511) (2832.8244 4397.2061) (2834.5191 4394.0611)
      (2839.145 4391.5115) (2845.4504 4389.8473) (2851.771 4388.9771) (2856.5038 4388.3969) (2858.6107 4387.3282)
      (2857.8779 4385.084) (2854.9466 4381.3282) (2851.084 4376.2595) (2847.8015 4370.626) (2846.3359 4365.542)
      (2847.3588 4362.1221) (2850.7786 4361.0992) (2855.8626 4362.5649) (2861.4962 4365.8473) (2866.5649 4369.6947)
      (2870.3206 4372.626) (2872.5649 4373.3588) (2873.6336 4371.2672) (2874.229 4366.5344) (2875.084 4360.2137)
      (2876.7481 4353.9084) (2879.2977 4349.2824) (2882.4427 4347.5878) (2885.5878 4349.2824) (2888.1374 4353.9084)
      (2889.8015 4360.2137) (2890.6565 4366.5344) (2891.2519 4371.2672) (2892.3206 4373.3588) (2894.5649 4372.626)
      (2898.3206 4369.6947) (2903.3893 4365.8473) (2909.0229 4362.5649) (2914.1069 4361.0992) (2917.5267 4362.1221)
      (2918.5496 4365.542) (2917.084 4370.626) (2913.8015 4376.2595) (2909.9389 4381.3282) (2907.0076 4385.084)
      (2906.2748 4387.3282) (2908.3817 4388.3969) (2913.1145 4388.9771) (2919.4351 4389.8473) (2925.7405 4391.5115)
      (2930.3664 4394.0611) (2931.2977 4395.7863) (2931.2977 4398.6107) (2930.3664 4400.3511) (2925.7405 4402.9008)
      (2919.4351 4404.5649) (2913.1145 4405.4198) (2908.3817 4406.0153) (2906.2748 4407.084) (2907.0076 4409.3282)
      (2909.2672 4412.2137)
    ))
    ; P2035 -- see feature_dimensions_mm.csv
    ("06_ORNAMENT" 0 (
      (2899.1756 4473.2824) (2900.7634 4475.0687) (2882.4427 4495.6794) (2864.1221 4475.0687) (2865.7099 4473.2824)
    ))
    ; P2036 -- see feature_dimensions_mm.csv
    ("06_ORNAMENT" 0 (
      (3054.9008 4473.2824) (3056.4885 4475.0687) (3038.1679 4495.6794) (3022.9008 4478.5038) (3022.9008 4473.2824)
    ))
    ; P2037 -- see feature_dimensions_mm.csv
    ("06_ORNAMENT" 0 (
      (3022.9008 4412.2137) (3022.9008 4370.1832) (3026.0458 4372.626) (3028.2901 4373.3588) (3029.3588 4371.2672)
      (3029.9542 4366.5344) (3030.8092 4360.2137) (3032.4733 4353.9084) (3035.0229 4349.2824) (3038.1679 4347.5878)
      (3041.313 4349.2824) (3043.8626 4353.9084) (3045.5267 4360.2137) (3046.3817 4366.5344) (3046.9771 4371.2672)
      (3048.0458 4373.3588) (3050.2901 4372.626) (3054.0458 4369.6947) (3059.1145 4365.8473) (3064.7481 4362.5649)
      (3069.8321 4361.0992) (3073.2519 4362.1221) (3074.2748 4365.542) (3072.8092 4370.626) (3069.5267 4376.2595)
      (3065.6641 4381.3282) (3062.7328 4385.084) (3062.0 4387.3282) (3064.1069 4388.3969) (3068.8397 4388.9771)
      (3075.1603 4389.8473) (3081.4656 4391.5115) (3086.0916 4394.0611) (3087.7863 4397.2061) (3086.0916 4400.3511)
      (3081.4656 4402.9008) (3075.1603 4404.5649) (3068.8397 4405.4198) (3064.1069 4406.0153) (3062.0 4407.084)
      (3062.7328 4409.3282) (3064.9924 4412.2137)
    ))
    ; P2038 -- see feature_dimensions_mm.csv
    ("06_ORNAMENT" 0 (
      (3038.6107 3832.0611) (3056.4885 3852.1679) (3038.1679 3872.7786) (3022.9008 3855.6031) (3022.9008 3848.7328)
      (3037.7252 3832.0611)
    ))
    ; P2039 -- see feature_dimensions_mm.csv
    ("06_ORNAMENT" 0 (
      (3167.0687 4412.2137) (3169.3282 4409.3282) (3170.0611 4407.084) (3167.9542 4406.0153) (3163.2214 4405.4198)
      (3156.9008 4404.5649) (3150.5954 4402.9008) (3145.9695 4400.3511) (3144.2748 4397.2061) (3145.9695 4394.0611)
      (3150.5954 4391.5115) (3156.9008 4389.8473) (3163.2214 4388.9771) (3167.9542 4388.3969) (3170.0611 4387.3282)
      (3169.3282 4385.084) (3166.3969 4381.3282) (3162.5344 4376.2595) (3159.2519 4370.626) (3157.7863 4365.542)
      (3158.8092 4362.1221) (3162.229 4361.0992) (3167.313 4362.5649) (3172.9466 4365.8473) (3178.0153 4369.6947)
      (3181.771 4372.626) (3184.0153 4373.3588) (3185.084 4371.2672) (3185.6794 4366.5344) (3186.5344 4360.2137)
      (3188.1985 4353.9084) (3190.7481 4349.2824) (3193.8931 4347.5878) (3197.0382 4349.2824) (3199.5878 4353.9084)
      (3201.2519 4360.2137) (3202.1069 4366.5344) (3202.7023 4371.2672) (3203.771 4373.3588) (3206.0153 4372.626)
      (3209.771 4369.6947) (3214.8397 4365.8473) (3220.4733 4362.5649) (3225.5573 4361.0992) (3228.9771 4362.1221)
      (3230.0 4365.542) (3228.5344 4370.626) (3225.2519 4376.2595) (3221.3893 4381.3282) (3218.458 4385.084)
      (3217.7252 4387.3282) (3219.8321 4388.3969) (3224.5649 4388.9771) (3230.8855 4389.8473) (3237.1908 4391.5115)
      (3241.8168 4394.0611) (3243.5115 4397.2061) (3241.8168 4400.3511) (3237.1908 4402.9008) (3230.8855 4404.5649)
      (3224.5649 4405.4198) (3219.8321 4406.0153) (3217.7252 4407.084) (3218.458 4409.3282) (3220.7176 4412.2137)
    ))
    ; P2040 -- see feature_dimensions_mm.csv
    ("06_ORNAMENT" 0 (
      (3210.626 4473.2824) (3212.2137 4475.0687) (3193.8931 4495.6794) (3175.5725 4475.0687) (3177.1603 4473.2824)
    ))
    ; P2041 -- see feature_dimensions_mm.csv
    ("06_ORNAMENT" 0 (
      (3194.3359 3832.0611) (3212.2137 3852.1679) (3193.8931 3872.7786) (3175.5725 3852.1679) (3193.4504 3832.0611)
    ))
    ; P2042 -- see feature_dimensions_mm.csv
    ("06_ORNAMENT" 0 (
      (3252.4275 5513.3435) (3235.9847 5517.8015) (3237.1145 5513.8626) (3240.3969 5508.229) (3244.2595 5503.1603)
      (3247.1908 5499.4046) (3247.9237 5497.1603) (3245.8168 5496.0916) (3241.084 5495.4962) (3234.7634 5494.6412)
      (3228.458 5492.9771) (3223.8321 5490.4275) (3222.1374 5487.2824) (3223.8321 5484.1374) (3228.458 5481.5878)
      (3234.7634 5479.9237) (3241.084 5479.0534) (3245.8168 5478.4733) (3247.9237 5477.4046) (3247.1908 5475.1603)
      (3244.2595 5471.4046) (3240.3969 5466.3359) (3237.1145 5460.7023) (3235.6489 5455.6183) (3236.6718 5452.1985)
      (3240.0916 5451.1756) (3245.1756 5452.6412) (3250.8092 5455.9237) (3255.8779 5459.771) (3259.6336 5462.7023)
      (3261.8779 5463.4351) (3262.9466 5461.3435) (3263.542 5456.6107) (3264.3969 5450.2901) (3266.0611 5443.9847)
      (3268.6107 5439.3588) (3271.7557 5437.6641) (3274.9008 5439.3588) (3277.4504 5443.9847) (3279.1145 5450.2901)
      (3279.9695 5456.6107) (3280.5649 5461.3435) (3281.6336 5463.4351) (3283.8779 5462.7023) (3287.6336 5459.771)
      (3292.7023 5455.9237) (3298.3359 5452.6412) (3303.4198 5451.1756) (3306.8397 5452.1985) (3307.8626 5455.6183)
      (3306.3969 5460.7023) (3303.1145 5466.3359) (3299.2519 5471.4046) (3296.3206 5475.1603) (3295.5878 5477.4046)
      (3297.6947 5478.4733) (3302.4275 5479.0534) (3308.7481 5479.9237) (3315.0534 5481.5878) (3319.6794 5484.1374)
      (3321.374 5487.2824) (3319.6794 5490.4275) (3315.0534 5492.9771) (3308.7481 5494.6412) (3302.4275 5495.4962)
      (3297.6947 5496.0916) (3295.5878 5497.1603) (3296.3206 5499.4046) (3296.9771 5500.229) (3292.4275 5501.6641)
    ))
    ; P2043 -- see feature_dimensions_mm.csv
    ("06_ORNAMENT" 0 (
      (3322.7939 4412.2137) (3325.0534 4409.3282) (3325.7863 4407.084) (3323.6794 4406.0153) (3318.9466 4405.4198)
      (3312.626 4404.5649) (3306.3206 4402.9008) (3301.6947 4400.3511) (3300.0 4397.2061) (3301.6947 4394.0611)
      (3306.3206 4391.5115) (3312.626 4389.8473) (3318.9466 4388.9771) (3323.6794 4388.3969) (3325.7863 4387.3282)
      (3325.0534 4385.084) (3322.1221 4381.3282) (3318.2595 4376.2595) (3314.9771 4370.626) (3313.5115 4365.542)
      (3314.5344 4362.1221) (3317.9542 4361.0992) (3323.0382 4362.5649) (3328.6718 4365.8473) (3333.7405 4369.6947)
      (3337.4962 4372.626) (3339.7405 4373.3588) (3340.8092 4371.2672) (3341.4046 4366.5344) (3342.2595 4360.2137)
      (3343.9237 4353.9084) (3346.4733 4349.2824) (3349.6183 4347.5878) (3352.7634 4349.2824) (3355.313 4353.9084)
      (3356.9771 4360.2137) (3357.8321 4366.5344) (3358.4275 4371.2672) (3359.4962 4373.3588) (3361.7405 4372.626)
      (3365.4962 4369.6947) (3370.5649 4365.8473) (3376.1985 4362.5649) (3381.2824 4361.0992) (3384.7023 4362.1221)
      (3385.7252 4365.542) (3384.2595 4370.626) (3380.9771 4376.2595) (3377.1145 4381.3282) (3374.1832 4385.084)
      (3373.4504 4387.3282) (3375.5573 4388.3969) (3380.2901 4388.9771) (3386.6107 4389.8473) (3392.916 4391.5115)
      (3397.542 4394.0611) (3399.2366 4397.2061) (3397.542 4400.3511) (3392.916 4402.9008) (3386.6107 4404.5649)
      (3380.2901 4405.4198) (3375.5573 4406.0153) (3373.4504 4407.084) (3374.1832 4409.3282) (3376.4427 4412.2137)
    ))
    ; P2044 -- see feature_dimensions_mm.csv
    ("06_ORNAMENT" 0 (
      (3366.3511 4473.2824) (3367.9389 4475.0687) (3349.6183 4495.6794) (3331.2977 4475.0687) (3332.8855 4473.2824)
    ))
    ; P2045 -- see feature_dimensions_mm.csv
    ("06_ORNAMENT" 0 (
      (3350.0611 3832.0611) (3367.9389 3852.1679) (3349.6183 3872.7786) (3331.2977 3852.1679) (3349.1756 3832.0611)
    ))
    ; P2046 -- see feature_dimensions_mm.csv
    ("06_ORNAMENT" 0 (
      (3419.8473 2839.6947) (3404.5802 2854.9618) (3389.313 2839.6947)
    ))
    ; P2047 -- see feature_dimensions_mm.csv
    ("06_ORNAMENT" 0 (
      (3411.2214 5460.7634) (3396.1832 5466.3969) (3396.1221 5466.3359) (3392.8397 5460.7023) (3391.374 5455.6183)
      (3392.3969 5452.1985) (3395.8168 5451.1756) (3400.9008 5452.6412) (3406.5344 5455.9237) (3411.6031 5459.771)
      (3412.3053 5460.3206)
    ))
    ; P2048 -- see feature_dimensions_mm.csv
    ("06_ORNAMENT" 0 (
      (3419.145 5457.5115) (3419.2672 5456.6107) (3420.1221 5450.2901) (3421.7863 5443.9847) (3424.3359 5439.3588)
      (3427.4809 5437.6641) (3430.626 5439.3588) (3433.1756 5443.9847) (3434.8397 5450.2901) (3434.9313 5451.0229)
    ))
    ; P2049 -- see feature_dimensions_mm.csv
    ("06_ORNAMENT" 0 (
      (3478.5191 4412.2137) (3480.7786 4409.3282) (3481.5115 4407.084) (3479.4046 4406.0153) (3474.6718 4405.4198)
      (3468.3511 4404.5649) (3462.0458 4402.9008) (3457.4198 4400.3511) (3455.7252 4397.2061) (3457.4198 4394.0611)
      (3462.0458 4391.5115) (3468.3511 4389.8473) (3474.6718 4388.9771) (3479.4046 4388.3969) (3481.5115 4387.3282)
      (3480.7786 4385.084) (3477.8473 4381.3282) (3473.9847 4376.2595) (3470.7023 4370.626) (3469.2366 4365.542)
      (3470.2595 4362.1221) (3473.6794 4361.0992) (3478.7634 4362.5649) (3484.3969 4365.8473) (3489.4656 4369.6947)
      (3493.2214 4372.626) (3495.4656 4373.3588) (3496.5344 4371.2672) (3497.1298 4366.5344) (3497.9847 4360.2137)
      (3499.6489 4353.9084) (3502.1985 4349.2824) (3505.3435 4347.5878) (3508.4885 4349.2824) (3511.0382 4353.9084)
      (3512.7023 4360.2137) (3513.5573 4366.5344) (3514.1527 4371.2672) (3515.2214 4373.3588) (3517.4656 4372.626)
      (3521.2214 4369.6947) (3526.2901 4365.8473) (3531.9237 4362.5649) (3537.0076 4361.0992) (3540.4275 4362.1221)
      (3541.4504 4365.542) (3539.9847 4370.626) (3536.7023 4376.2595) (3532.8397 4381.3282) (3529.9084 4385.084)
      (3529.1756 4387.3282) (3531.2824 4388.3969) (3536.0153 4388.9771) (3542.3359 4389.8473) (3548.6412 4391.5115)
      (3553.2672 4394.0611) (3554.9618 4397.2061) (3553.2672 4400.3511) (3548.6412 4402.9008) (3542.3359 4404.5649)
      (3536.0153 4405.4198) (3531.2824 4406.0153) (3529.1756 4407.084) (3529.9084 4409.3282) (3532.1679 4412.2137)
    ))
    ; P2050 -- see feature_dimensions_mm.csv
    ("06_ORNAMENT" 0 (
      (3522.0763 4473.2824) (3523.6641 4475.0687) (3505.3435 4495.6794) (3487.0229 4475.0687) (3488.6107 4473.2824)
    ))
    ; P2051 -- see feature_dimensions_mm.csv
    ("06_ORNAMENT" 0 (
      (3505.7863 3832.0611) (3523.6641 3852.1679) (3505.3435 3872.7786) (3487.0229 3852.1679) (3504.9008 3832.0611)
    ))
    ; P2052 -- see feature_dimensions_mm.csv
    ("06_ORNAMENT" 0 (
      (3625.1603 5339.0534) (3624.0763 5338.916) (3617.771 5337.2519) (3613.145 5334.7023) (3611.4504 5331.5573)
      (3613.145 5328.4122) (3617.771 5325.8626) (3624.0763 5324.1985) (3630.3969 5323.3282) (3635.1298 5322.7481)
      (3637.2366 5321.6794) (3636.5038 5319.4351) (3633.5725 5315.6794) (3629.7099 5310.6107) (3626.4275 5304.9771)
      (3624.9618 5299.8931) (3625.9847 5296.4733) (3629.4046 5295.4504) (3634.4885 5296.916) (3640.1221 5300.1985)
      (3645.1908 5304.0458) (3648.9466 5306.9771) (3651.1908 5307.7099) (3652.2595 5305.6183) (3652.855 5300.8855)
      (3653.7099 5294.5649) (3655.374 5288.2595) (3657.9237 5283.6336) (3661.0687 5281.9389) (3664.2137 5283.6336)
      (3666.7634 5288.2595) (3667.3588 5290.5038)
    ))
    ; P2053 -- see feature_dimensions_mm.csv
    ("06_ORNAMENT" 0 (
      (3677.8015 4473.2824) (3679.3893 4475.0687) (3661.0687 4495.6794) (3642.7481 4475.0687) (3644.3359 4473.2824)
    ))
    ; P2054 -- see feature_dimensions_mm.csv
    ("06_ORNAMENT" 0 (
      (3709.9237 2839.6947) (3694.6565 2854.9618) (3679.3893 2839.6947)
    ))
    ; P2055 -- see feature_dimensions_mm.csv
    ("06_ORNAMENT" 0 (
      (3801.5267 3832.0611) (3908.3969 3832.0611) (3923.6641 3832.0611) (3923.6641 4412.2137) (3908.3969 4412.2137)
      (3801.5267 4412.2137)
    ))
    ; P2056 -- see feature_dimensions_mm.csv
    ("06_ORNAMENT" 0 (
      (4000.0 2839.6947) (3984.7328 2854.9618) (3969.4656 2839.6947)
    ))
    ; P2057 -- see feature_dimensions_mm.csv
    ("06_ORNAMENT" 0 (
      (3984.7328 4473.2824) (3984.7328 3679.3893) (3984.7328 3633.5878)
    ))
    ; P2058 -- see feature_dimensions_mm.csv
    ("06_ORNAMENT" 0 (
      (4595.4198 3633.5878) (4595.4198 3664.1221) (4595.4198 3679.3893) (4595.4198 3740.458)
    ))
    ; P2059 -- see feature_dimensions_mm.csv
    ("06_ORNAMENT" 0 (
      (9048.855 4412.2137) (9050.3053 4411.4046) (9056.3206 4409.8321) (9062.3511 4409.0076) (9066.855 4408.4427)
      (9068.8702 4407.4198) (9068.1679 4405.2824) (9065.374 4401.6947) (9061.6947 4396.855) (9058.5649 4391.4962)
      (9057.1603 4386.6412) (9058.1374 4383.374) (9061.4046 4382.4122) (9066.2443 4383.8015) (9071.6183 4386.9313)
      (9076.458 4390.6107) (9080.0458 4393.4046) (9082.1832 4394.1069) (9083.2061 4392.1069) (9083.771 4387.5878)
      (9084.5802 4381.5725) (9086.1679 4375.5573) (9088.6107 4371.1298) (9091.6031 4369.5115) (9094.5954 4371.1298)
      (9097.0382 4375.5573) (9098.626 4381.5725) (9099.4504 4387.5878) (9100.0 4392.1069) (9101.0229 4394.1069)
      (9103.1603 4393.4046) (9106.7481 4390.6107) (9111.5878 4386.9313) (9116.9618 4383.8015) (9121.8015 4382.4122)
      (9125.0687 4383.374) (9126.0458 4386.6412) (9124.6412 4391.4962) (9121.5115 4396.855) (9117.8321 4401.6947)
      (9115.0382 4405.2824) (9114.3359 4407.4198) (9116.3511 4408.4427) (9120.855 4409.0076) (9126.8855 4409.8321)
      (9132.9008 4411.4046) (9134.3511 4412.2137)
    ))
    ; P2060 -- see feature_dimensions_mm.csv
    ("06_ORNAMENT" 0 (
      (9134.3511 3832.0611) (9137.313 3833.6947) (9138.9313 3836.687) (9137.313 3839.6947) (9132.9008 3842.1221)
      (9126.8855 3843.7099) (9120.855 3844.5344) (9116.3511 3845.0992) (9114.3359 3846.1069) (9115.0382 3848.2443)
      (9117.8321 3851.8321) (9121.5115 3856.6718) (9124.6412 3862.0458) (9126.0458 3866.9008) (9125.0687 3870.1527)
      (9121.8015 3871.1298) (9116.9618 3869.7405) (9111.5878 3866.5954) (9106.7481 3862.9313) (9103.1603 3860.1374)
      (9101.0229 3859.4351) (9100.0 3861.4351) (9099.4504 3865.9542) (9098.626 3871.9695) (9097.0382 3877.9847)
      (9094.5954 3882.3969) (9091.6031 3884.0153) (9088.6107 3882.3969) (9086.1679 3877.9847) (9084.5802 3871.9695)
      (9083.771 3865.9542) (9083.2061 3861.4351) (9082.1832 3859.4351) (9080.0458 3860.1374) (9076.458 3862.9313)
      (9071.6183 3866.5954) (9066.2443 3869.7405) (9061.4046 3871.1298) (9058.1374 3870.1527) (9057.1603 3866.9008)
      (9058.5649 3862.0458) (9061.6947 3856.6718) (9065.374 3851.8321) (9068.1679 3848.2443) (9068.8702 3846.1069)
      (9066.855 3845.0992) (9062.3511 3844.5344) (9056.3206 3843.7099) (9050.3053 3842.1221) (9045.8931 3839.6947)
      (9044.2748 3836.687) (9045.8931 3833.6947) (9048.855 3832.0611)
    ))
    ; P2061 -- see feature_dimensions_mm.csv
    ("06_ORNAMENT" 0 (
      (9080.6565 4412.2137) (9083.1756 4408.4275) (9087.0534 4405.8473) (9091.6031 4404.9313) (9096.1527 4405.8473)
      (9100.0305 4408.4275) (9102.5496 4412.2137)
    ))
    ; P2062 -- see feature_dimensions_mm.csv
    ("06_ORNAMENT" 0 (
      (9102.5496 3832.0611) (9102.6107 3832.1374) (9103.5115 3836.687) (9102.6107 3841.2519) (9100.0305 3845.1145)
      (9096.1527 3847.6947) (9091.6031 3848.5954) (9087.0534 3847.6947) (9083.1756 3845.1145) (9080.5954 3841.2519)
      (9079.6947 3836.687) (9080.5954 3832.1374) (9080.6565 3832.0611)
    ))
    ; P2063 -- see feature_dimensions_mm.csv
    ("06_ORNAMENT" 0 (
      (9095.6336 4473.2824) (9109.9237 4489.3588) (9091.6031 4509.9695) (9073.2824 4489.3588) (9087.5725 4473.2824)
    ))
    ; P2064 -- see feature_dimensions_mm.csv
    ("06_ORNAMENT" 0 (
      (9131.9542 5405.313) (9130.4427 5404.5496) (9129.6794 5401.9084) (9130.6565 5398.6412) (9133.9237 5397.6794)
      (9138.7634 5399.0687) (9144.1374 5402.1985) (9148.9771 5405.8779) (9152.5649 5408.6718) (9154.7023 5409.374)
      (9155.7252 5407.374) (9156.2901 5402.855) (9157.0992 5396.8397) (9158.687 5390.8244) (9161.1298 5386.3969)
      (9164.1221 5384.7786) (9167.1145 5386.3969) (9169.5573 5390.8244) (9171.145 5396.8397) (9171.9695 5402.855)
      (9172.5191 5407.374) (9173.542 5409.374) (9175.6794 5408.6718) (9179.2672 5405.8779) (9184.1069 5402.1985)
      (9189.4809 5399.0687) (9194.3206 5397.6794) (9197.5878 5398.6412) (9198.5649 5401.9084) (9197.1603 5406.7634)
      (9194.0305 5412.1221) (9190.3511 5416.9618) (9187.5573 5420.5496) (9186.855 5422.687) (9188.8702 5423.7099)
      (9193.374 5424.2748) (9199.4046 5425.0992) (9205.4198 5426.6718) (9209.8321 5429.1145) (9211.4504 5432.1069)
      (9209.8321 5435.1145) (9206.7634 5436.8092)
    ))
    ; P2065 -- see feature_dimensions_mm.csv
    ("06_ORNAMENT" 0 (
      (9193.8931 4412.2137) (9195.3435 4411.4046) (9201.3588 4409.8321) (9207.3893 4409.0076) (9211.8931 4408.4427)
      (9213.9084 4407.4198) (9213.2061 4405.2824) (9210.4122 4401.6947) (9206.7328 4396.855) (9203.6031 4391.4962)
      (9202.1985 4386.6412) (9203.1756 4383.374) (9206.4427 4382.4122) (9211.2824 4383.8015) (9216.6565 4386.9313)
      (9221.4962 4390.6107) (9225.084 4393.4046) (9227.2214 4394.1069) (9228.2443 4392.1069) (9228.8092 4387.5878)
      (9229.6183 4381.5725) (9231.2061 4375.5573) (9233.6489 4371.1298) (9236.6412 4369.5115) (9239.6336 4371.1298)
      (9242.0763 4375.5573) (9243.6641 4381.5725) (9244.4885 4387.5878) (9245.0382 4392.1069) (9246.0611 4394.1069)
      (9248.1985 4393.4046) (9251.7863 4390.6107) (9256.626 4386.9313) (9262.0 4383.8015) (9266.8397 4382.4122)
      (9270.1069 4383.374) (9271.084 4386.6412) (9269.6794 4391.4962) (9266.5496 4396.855) (9262.8702 4401.6947)
      (9260.0763 4405.2824) (9259.374 4407.4198) (9261.3893 4408.4427) (9265.8931 4409.0076) (9271.9237 4409.8321)
      (9277.9389 4411.4046) (9279.3893 4412.2137)
    ))
    ; P2066 -- see feature_dimensions_mm.csv
    ("06_ORNAMENT" 0 (
      (9279.3893 3832.0611) (9282.3511 3833.6947) (9283.9695 3836.687) (9282.3511 3839.6947) (9277.9389 3842.1221)
      (9271.9237 3843.7099) (9265.8931 3844.5344) (9261.3893 3845.0992) (9259.374 3846.1069) (9260.0763 3848.2443)
      (9262.8702 3851.8321) (9266.5496 3856.6718) (9269.6794 3862.0458) (9271.084 3866.9008) (9270.1069 3870.1527)
      (9266.8397 3871.1298) (9262.0 3869.7405) (9256.626 3866.5954) (9251.7863 3862.9313) (9248.1985 3860.1374)
      (9246.0611 3859.4351) (9245.0382 3861.4351) (9244.4885 3865.9542) (9243.6641 3871.9695) (9242.0763 3877.9847)
      (9239.6336 3882.3969) (9236.6412 3884.0153) (9233.6489 3882.3969) (9231.2061 3877.9847) (9229.6183 3871.9695)
      (9228.8092 3865.9542) (9228.2443 3861.4351) (9227.2214 3859.4351) (9225.084 3860.1374) (9221.4962 3862.9313)
      (9216.6565 3866.5954) (9211.2824 3869.7405) (9206.4427 3871.1298) (9203.1756 3870.1527) (9202.1985 3866.9008)
      (9203.6031 3862.0458) (9206.7328 3856.6718) (9210.4122 3851.8321) (9213.2061 3848.2443) (9213.9084 3846.1069)
      (9211.8931 3845.0992) (9207.3893 3844.5344) (9201.3588 3843.7099) (9195.3435 3842.1221) (9190.9313 3839.6947)
      (9189.313 3836.687) (9190.9313 3833.6947) (9193.8931 3832.0611)
    ))
    ; P2067 -- see feature_dimensions_mm.csv
    ("06_ORNAMENT" 0 (
      (9225.6947 4412.2137) (9228.2137 4408.4275) (9232.0916 4405.8473) (9236.6412 4404.9313) (9241.1908 4405.8473)
      (9245.0687 4408.4275) (9247.5878 4412.2137)
    ))
    ; P2068 -- see feature_dimensions_mm.csv
    ("06_ORNAMENT" 0 (
      (9247.5878 3832.0611) (9247.6489 3832.1374) (9248.5496 3836.687) (9247.6489 3841.2519) (9245.0687 3845.1145)
      (9241.1908 3847.6947) (9236.6412 3848.5954) (9232.0916 3847.6947) (9228.2137 3845.1145) (9225.6336 3841.2519)
      (9224.7328 3836.687) (9225.6336 3832.1374) (9225.6947 3832.0611)
    ))
    ; P2069 -- see feature_dimensions_mm.csv
    ("06_ORNAMENT" 0 (
      (9240.6718 4473.2824) (9254.9618 4489.3588) (9236.6412 4509.9695) (9218.3206 4489.3588) (9232.6107 4473.2824)
    ))
    ; P2070 -- see feature_dimensions_mm.csv
    ("06_ORNAMENT" 0 (
      (9276.2901 2782.4733) (9274.687 2810.7786) (9270.7328 2844.1527) (9264.8702 2877.6489) (9257.313 2910.855)
      (9248.3053 2943.3282) (9238.0305 2974.6565) (9226.7328 3004.4122) (9214.626 3032.1832) (9201.9084 3057.5267)
      (9188.8244 3080.0153) (9175.5725 3099.2366) (9172.2443 3073.8015) (9170.9466 3054.8397) (9166.4885 3056.1832)
      (9157.1908 3057.8473) (9149.1908 3058.855) (9143.4656 3059.9695) (9140.4885 3061.9847) (9140.229 3065.5573)
      (9142.1374 3071.084) (9145.2519 3078.5191) (9148.458 3087.3893) (9150.687 3096.8397) (9151.084 3105.7405)
      (9149.2061 3112.9466) (9145.0382 3117.4962) (9139.0076 3118.8244) (9131.8321 3116.855) (9124.3206 3112.0611)
      (9117.2519 3105.4198) (9111.1756 3098.1985) (9106.2901 3091.771) (9102.458 3087.374) (9099.2366 3085.8015)
      (9096.0153 3087.374) (9092.1832 3091.771) (9087.2977 3098.1985) (9081.2214 3105.4198) (9074.1527 3112.0611)
      (9066.6412 3116.855) (9059.4656 3118.8244) (9053.4351 3117.4962) (9049.2672 3112.9466) (9047.3893 3105.7405)
      (9047.7863 3096.8397) (9050.0153 3087.3893) (9053.2214 3078.5191) (9056.3359 3071.084) (9058.2443 3065.5573)
      (9057.9847 3061.9847) (9055.0076 3059.9695) (9049.2824 3058.855) (9041.2824 3057.8473) (9031.9847 3056.1832)
      (9022.7023 3053.3893) (9014.7939 3049.2824) (9009.4962 3044.0458) (9007.6336 3038.1679) (9009.4962 3032.2901)
      (9014.7939 3027.0534) (9022.7023 3022.9466) (9031.9847 3020.1527) (9041.2824 3018.4885) (9049.2824 3017.4809)
      (9055.0076 3016.3664) (9057.9847 3014.3511) (9058.2443 3010.7786) (9056.3359 3005.2519) (9053.2214 2997.8168)
      (9050.0153 2988.9466) (9047.7863 2979.4962) (9047.3893 2970.5954) (9049.2672 2963.3893) (9053.4351 2958.8397)
      (9059.4656 2957.5115) (9066.6412 2959.4809) (9074.1527 2964.2748) (9075.5115 2965.5573) (9076.855 2941.9084)
      (9079.7099 2917.1908) (9084.0763 2892.4733) (9090.0 2868.0763) (9097.5267 2844.3817) (9106.6718 2821.6947)
      (9117.4809 2800.3969) (9130.0 2780.7939) (9144.2595 2763.2366) (9160.3053 2748.0916) (9167.0229 2770.2748)
      (9171.0534 2793.6031) (9172.626 2817.8015) (9171.9237 2842.5496) (9169.145 2867.5573) (9164.5038 2892.4885)
      (9158.1832 2917.0687) (9150.3969 2940.9924) (9143.4809 2958.5038) (9145.0382 2958.8397) (9149.2061 2963.3893)
      (9151.084 2970.5954) (9150.687 2979.4962) (9148.458 2988.9466) (9145.2519 2997.8168) (9142.1374 3005.2519)
      (9140.229 3010.7786) (9140.4885 3014.3511) (9143.4656 3016.3664) (9149.1908 3017.4809) (9157.1908 3018.4885)
      (9166.4885 3020.1527) (9169.9695 3021.1908) (9169.8931 3016.1527) (9170.9008 2984.8244) (9173.4198 2952.4275)
      (9177.4504 2919.4198) (9183.0229 2886.229) (9190.1679 2853.3282) (9198.9008 2821.1603) (9209.2366 2790.1679)
      (9221.2061 2760.8092) (9222.3817 2758.4733) (9244.2901 2768.6718)
    ))
    ; P2071 -- see feature_dimensions_mm.csv
    ("06_ORNAMENT" 0 (
      (9275.2672 5460.4275) (9276.1221 5457.4656) (9279.2519 5452.0916) (9282.9313 5447.2519) (9285.7252 5443.6641)
      (9286.4275 5441.5267) (9284.4122 5440.5191) (9279.9084 5439.9542) (9273.8779 5439.1298) (9267.8626 5437.542)
      (9263.4504 5435.1145) (9261.8321 5432.1069) (9263.4504 5429.1145) (9267.8626 5426.6718) (9273.8779 5425.0992)
      (9279.9084 5424.2748) (9284.4122 5423.7099) (9286.4275 5422.687) (9285.7252 5420.5496) (9282.9313 5416.9618)
      (9279.2519 5412.1221) (9276.1221 5406.7634) (9274.7176 5401.9084) (9275.6947 5398.6412) (9278.9618 5397.6794)
      (9283.8015 5399.0687) (9289.1756 5402.1985) (9294.0153 5405.8779) (9297.6031 5408.6718) (9299.7405 5409.374)
      (9300.7634 5407.374) (9301.3282 5402.855) (9302.1374 5396.8397) (9303.7252 5390.8244) (9306.1679 5386.3969)
      (9309.1603 5384.7786) (9312.1527 5386.3969) (9314.5954 5390.8244) (9316.1832 5396.8397) (9317.0076 5402.855)
      (9317.5573 5407.374) (9318.5802 5409.374) (9320.7176 5408.6718) (9324.3053 5405.8779) (9329.145 5402.1985)
      (9334.5191 5399.0687) (9339.3588 5397.6794) (9342.626 5398.6412) (9343.6031 5401.9084) (9342.1985 5406.7634)
      (9339.0687 5412.1221) (9335.3893 5416.9618) (9332.5954 5420.5496) (9331.8931 5422.687) (9333.9084 5423.7099)
      (9338.4122 5424.2748) (9344.4427 5425.0992) (9350.458 5426.6718) (9354.8702 5429.1145) (9356.4885 5432.1069)
      (9354.8702 5435.1145) (9350.458 5437.542) (9344.4427 5439.1298) (9338.4122 5439.9542) (9333.9084 5440.5191)
      (9331.8931 5441.5267) (9332.5954 5443.6641) (9335.3893 5447.2519) (9339.0687 5452.0916) (9342.1985 5457.4656)
      (9343.6031 5462.3206) (9342.626 5465.5725) (9339.3588 5466.5496) (9334.5191 5465.1603) (9329.145 5462.0153)
      (9324.3053 5458.3511) (9320.7176 5455.5573) (9318.5802 5454.855) (9317.5573 5456.855) (9317.0076 5461.374)
      (9316.1832 5467.3893) (9314.8855 5472.2901)
    ))
    ; P2072 -- see feature_dimensions_mm.csv
    ("06_ORNAMENT" 0 (
      (9302.4885 5468.6718) (9302.1374 5467.3893) (9301.3282 5461.374) (9300.7634 5456.855) (9299.7405 5454.855)
      (9297.6031 5455.5573) (9294.0153 5458.3511) (9289.1756 5462.0153) (9286.1374 5463.8015) (9280.5954 5462.1374)
    ))
    ; P2073 -- see feature_dimensions_mm.csv
    ("06_ORNAMENT" 0 (
      (9316.0611 2798.5191) (9350.5649 2811.3588) (9372.4733 2818.916) (9372.2137 2821.1298) (9365.1145 2863.2061)
      (9356.3359 2905.0229) (9346.0916 2946.0458) (9334.6412 2985.7405) (9322.1832 3023.542) (9308.9771 3058.916)
      (9306.626 3064.4733) (9306.9466 3064.3817) (9312.9771 3065.7099) (9317.145 3070.2595) (9319.0229 3077.4656)
      (9318.626 3086.3664) (9316.3969 3095.8168) (9313.1908 3104.687) (9310.0763 3112.1221) (9308.1679 3117.6489)
      (9308.4275 3121.2214) (9311.4046 3123.2366) (9317.1298 3124.3511) (9325.1298 3125.3588) (9334.4275 3127.0229)
      (9343.7099 3129.8168) (9351.6183 3133.9237) (9356.916 3139.1603) (9358.7786 3145.0382) (9356.916 3150.916)
      (9351.6183 3156.1527) (9343.7099 3160.2595) (9334.4275 3163.0534) (9325.1298 3164.7176) (9317.1298 3165.7252)
      (9311.4046 3166.8397) (9308.4275 3168.855) (9308.1679 3172.4275) (9310.0763 3177.9542) (9313.1908 3185.3893)
      (9316.3969 3194.2595) (9318.626 3203.7099) (9319.0229 3212.6107) (9317.145 3219.8168) (9312.9771 3224.3664)
      (9306.9466 3225.6947) (9299.771 3223.7252) (9292.2595 3218.9313) (9285.1908 3212.2901) (9279.1145 3205.0687)
      (9274.229 3198.6412) (9270.3969 3194.2443) (9267.1756 3192.6718) (9263.9542 3194.2443) (9260.1221 3198.6412)
      (9255.2366 3205.0687) (9249.1603 3212.2901) (9242.0916 3218.9313) (9234.5802 3223.7252) (9227.4046 3225.6947)
      (9221.374 3224.3664) (9217.2061 3219.8168) (9215.3282 3212.6107) (9215.7252 3203.7099) (9217.9542 3194.2595)
      (9221.1603 3185.3893) (9224.2748 3177.9542) (9226.1832 3172.4275) (9225.9237 3168.855) (9222.9466 3166.8397)
      (9217.2214 3165.7252) (9209.2214 3164.7176) (9199.9237 3163.0534) (9190.6412 3160.2595) (9182.7328 3156.1527)
      (9177.4351 3150.916) (9175.5725 3145.0382) (9177.4351 3139.1603) (9182.7328 3133.9237) (9190.6412 3129.8168)
      (9199.9237 3127.0229) (9209.2214 3125.3588) (9217.2214 3124.3511) (9222.9466 3123.2366) (9225.9237 3121.2214)
      (9226.1832 3117.6489) (9224.2748 3112.1221) (9221.1603 3104.687) (9217.9542 3095.8168) (9215.7252 3086.3664)
      (9215.3282 3077.4656) (9217.2061 3070.2595) (9221.374 3065.7099) (9227.4046 3064.3817) (9234.5802 3066.3511)
      (9242.0916 3071.145) (9249.1603 3077.7863) (9255.2366 3085.0076) (9260.1221 3091.4351) (9263.9542 3095.8321)
      (9264.1985 3095.9542) (9263.7252 3079.145) (9264.3053 3042.0916) (9266.4122 3003.0687) (9270.0763 2962.5954)
      (9275.2977 2921.2519) (9282.0763 2879.5878) (9290.4427 2838.1679) (9300.3664 2797.5573) (9301.771 2792.7939)
    ))
    ; P2074 -- see feature_dimensions_mm.csv
    ("06_ORNAMENT" 0 (
      (9392.626 3832.0611) (9424.4275 3832.0611) (9427.3893 3833.6947) (9429.0076 3836.687) (9427.3893 3839.6947)
      (9422.9771 3842.1221) (9416.9618 3843.7099) (9410.9313 3844.5344) (9406.4275 3845.0992) (9404.4122 3846.1069)
      (9405.1145 3848.2443) (9407.9084 3851.8321) (9411.5878 3856.6718) (9414.7176 3862.0458) (9416.1221 3866.9008)
      (9415.145 3870.1527) (9411.8779 3871.1298) (9407.0382 3869.7405) (9401.6641 3866.5954) (9396.8244 3862.9313)
      (9393.2366 3860.1374) (9391.0992 3859.4351) (9390.0763 3861.4351) (9389.5267 3865.9542) (9388.7023 3871.9695)
      (9387.1145 3877.9847) (9384.6718 3882.3969) (9381.6794 3884.0153) (9378.687 3882.3969) (9376.2443 3877.9847)
      (9374.6565 3871.9695) (9373.8473 3865.9542) (9373.2824 3861.4351) (9372.2595 3859.4351) (9370.1221 3860.1374)
      (9366.5344 3862.9313) (9361.6947 3866.5954) (9356.3206 3869.7405) (9351.4809 3871.1298) (9348.2137 3870.1527)
      (9347.2366 3866.9008) (9348.6412 3862.0458) (9351.771 3856.6718) (9355.4504 3851.8321) (9358.2443 3848.2443)
      (9358.9466 3846.1069) (9356.9313 3845.0992) (9352.4275 3844.5344) (9346.3969 3843.7099) (9340.3817 3842.1221)
      (9335.9695 3839.6947) (9334.3511 3836.687) (9335.9695 3833.6947) (9338.9313 3832.0611)
    ))
    ; P2075 -- see feature_dimensions_mm.csv
    ("06_ORNAMENT" 0 (
      (9385.7099 4473.2824) (9400.0 4489.3588) (9381.6794 4509.9695) (9363.3588 4489.3588) (9377.6489 4473.2824)
    ))
    ; P2076 -- see feature_dimensions_mm.csv
    ("06_ORNAMENT" 0 (
      (9392.626 4412.2137) (9390.1069 4408.4275) (9386.229 4405.8473) (9381.6794 4404.9313) (9377.1298 4405.8473)
      (9373.2519 4408.4275) (9370.7328 4412.2137) (9338.9313 4412.2137) (9340.3817 4411.4046) (9346.3969 4409.8321)
      (9352.4275 4409.0076) (9356.9313 4408.4427) (9358.9466 4407.4198) (9358.2443 4405.2824) (9355.4504 4401.6947)
      (9351.771 4396.855) (9348.6412 4391.4962) (9347.2366 4386.6412) (9348.2137 4383.374) (9351.4809 4382.4122)
      (9356.3206 4383.8015) (9361.6947 4386.9313) (9366.5344 4390.6107) (9370.1221 4393.4046) (9372.2595 4394.1069)
      (9373.2824 4392.1069) (9373.8473 4387.5878) (9374.6565 4381.5725) (9376.2443 4375.5573) (9378.687 4371.1298)
      (9381.6794 4369.5115) (9384.6718 4371.1298) (9387.1145 4375.5573) (9388.7023 4381.5725) (9389.5267 4387.5878)
      (9390.0763 4392.1069) (9391.0992 4394.1069) (9393.2366 4393.4046) (9396.8244 4390.6107) (9401.6641 4386.9313)
      (9407.0382 4383.8015) (9411.8779 4382.4122) (9415.145 4383.374) (9416.1221 4386.6412) (9414.7176 4391.4962)
      (9411.5878 4396.855) (9407.9084 4401.6947) (9405.1145 4405.2824) (9404.4122 4407.4198) (9406.4275 4408.4427)
      (9410.9313 4409.0076) (9416.9618 4409.8321) (9422.9771 4411.4046) (9424.4275 4412.2137)
    ))
    ; P2077 -- see feature_dimensions_mm.csv
    ("06_ORNAMENT" 1 (
      (9392.626 3832.0611) (9392.687 3832.1374) (9393.5878 3836.687) (9392.687 3841.2519) (9390.1069 3845.1145)
      (9386.229 3847.6947) (9381.6794 3848.5954) (9377.1298 3847.6947) (9373.2519 3845.1145) (9370.6718 3841.2519)
      (9369.771 3836.687) (9370.6718 3832.1374) (9370.7328 3832.0611)
    ))
    ; P2078 -- see feature_dimensions_mm.csv
    ("06_ORNAMENT" 0 (
      (9450.3817 5420.9618) (9450.3817 5443.2672)
    ))
    ; P2079 -- see feature_dimensions_mm.csv
    ("06_ORNAMENT" 0 (
      (9450.3817 5443.2672) (9449.6489 5443.1145) (9445.771 5440.5344) (9443.1908 5436.6718) (9442.2901 5432.1069)
      (9443.1908 5427.5573) (9445.771 5423.6947) (9449.6489 5421.1145) (9450.3817 5420.9618)
    ))
    ; P2080 -- see feature_dimensions_mm.csv
    ("06_ORNAMENT" 0 (
      (9450.3817 5443.2672) (9450.3817 5476.3359) (9448.7634 5473.4046) (9447.1756 5467.3893) (9446.3664 5461.374)
      (9445.8015 5456.855) (9444.7786 5454.855) (9442.6412 5455.5573) (9439.0534 5458.3511) (9434.2137 5462.0153)
      (9428.8397 5465.1603) (9424.0 5466.5496) (9420.7328 5465.5725) (9419.7557 5462.3206) (9421.1603 5457.4656)
      (9424.2901 5452.0916) (9427.9695 5447.2519) (9430.7634 5443.6641) (9431.4656 5441.5267) (9429.4504 5440.5191)
      (9424.9466 5439.9542) (9418.916 5439.1298) (9412.9008 5437.542) (9408.4885 5435.1145) (9406.8702 5432.1069)
      (9408.4885 5429.1145) (9412.9008 5426.6718) (9418.916 5425.0992) (9424.9466 5424.2748) (9429.4504 5423.7099)
      (9431.4656 5422.687) (9430.7634 5420.5496) (9427.9695 5416.9618) (9424.2901 5412.1221) (9421.1603 5406.7634)
      (9419.7557 5401.9084) (9420.7328 5398.6412) (9424.0 5397.6794) (9428.8397 5399.0687) (9434.2137 5402.1985)
      (9439.0534 5405.8779) (9442.6412 5408.6718) (9444.7786 5409.374) (9445.8015 5407.374) (9446.3664 5402.855)
      (9447.1756 5396.8397) (9448.7634 5390.8244) (9450.3817 5387.8931) (9450.3817 5420.9618)
    ))
    ; P2081 -- see feature_dimensions_mm.csv
    ("06_ORNAMENT" 0 (
      (9450.3817 5130.8855) (9450.3817 5153.1908)
    ))
    ; P2082 -- see feature_dimensions_mm.csv
    ("06_ORNAMENT" 0 (
      (9450.3817 5153.1908) (9449.6489 5153.0382) (9445.771 5150.458) (9443.1908 5146.5954) (9442.2901 5142.0305)
      (9443.1908 5137.4809) (9445.771 5133.6183) (9449.6489 5131.0382) (9450.3817 5130.8855)
    ))
    ; P2083 -- see feature_dimensions_mm.csv
    ("06_ORNAMENT" 0 (
      (9450.3817 5153.1908) (9450.3817 5186.2595) (9448.7634 5183.3282) (9447.1756 5177.313) (9446.3664 5171.2977)
      (9445.8015 5166.7786) (9444.7786 5164.7786) (9442.6412 5165.4809) (9439.0534 5168.2748) (9434.2137 5171.9389)
      (9428.8397 5175.084) (9424.0 5176.4733) (9420.7328 5175.4962) (9419.7557 5172.2443) (9421.1603 5167.3893)
      (9424.2901 5162.0153) (9427.9695 5157.1756) (9430.7634 5153.5878) (9431.4656 5151.4504) (9429.4504 5150.4427)
      (9424.9466 5149.8779) (9418.916 5149.0534) (9412.9008 5147.4656) (9408.4885 5145.0382) (9406.8702 5142.0305)
      (9408.4885 5139.0382) (9412.9008 5136.5954) (9418.916 5135.0229) (9424.9466 5134.1985) (9429.4504 5133.6336)
      (9431.4656 5132.6107) (9430.7634 5130.4733) (9427.9695 5126.8855) (9424.2901 5122.0458) (9421.1603 5116.687)
      (9419.7557 5111.8321) (9420.7328 5108.5649) (9424.0 5107.6031) (9428.8397 5108.9924) (9434.2137 5112.1221)
      (9439.0534 5115.8015) (9442.6412 5118.5954) (9444.7786 5119.2977) (9445.8015 5117.2977) (9446.3664 5112.7786)
      (9447.1756 5106.7634) (9448.7634 5100.7481) (9450.3817 5097.8168) (9450.3817 5130.8855)
    ))
    ; P2084 -- see feature_dimensions_mm.csv
    ("06_ORNAMENT" 0 (
      (9450.3817 4840.8092) (9450.3817 4863.1145)
    ))
    ; P2085 -- see feature_dimensions_mm.csv
    ("06_ORNAMENT" 0 (
      (9450.3817 4863.1145) (9449.6489 4862.9618) (9445.771 4860.3817) (9443.1908 4856.5191) (9442.2901 4851.9542)
      (9443.1908 4847.4046) (9445.771 4843.542) (9449.6489 4840.9618) (9450.3817 4840.8092)
    ))
    ; P2086 -- see feature_dimensions_mm.csv
    ("06_ORNAMENT" 0 (
      (9450.3817 4863.1145) (9450.3817 4896.1832) (9448.7634 4893.2519) (9447.1756 4887.2366) (9446.3664 4881.2214)
      (9445.8015 4876.7023) (9444.7786 4874.7023) (9442.6412 4875.4046) (9439.0534 4878.1985) (9434.2137 4881.8626)
      (9428.8397 4885.0076) (9424.0 4886.3969) (9420.7328 4885.4198) (9419.7557 4882.1679) (9421.1603 4877.313)
      (9424.2901 4871.9389) (9427.9695 4867.0992) (9430.7634 4863.5115) (9431.4656 4861.374) (9429.4504 4860.3664)
      (9424.9466 4859.8015) (9418.916 4858.9771) (9412.9008 4857.3893) (9408.4885 4854.9618) (9406.8702 4851.9542)
      (9408.4885 4848.9618) (9412.9008 4846.5191) (9418.916 4844.9466) (9424.9466 4844.1221) (9429.4504 4843.5573)
      (9431.4656 4842.5344) (9430.7634 4840.3969) (9427.9695 4836.8092) (9424.2901 4831.9695) (9421.1603 4826.6107)
      (9419.7557 4821.7557) (9420.7328 4818.4885) (9424.0 4817.5267) (9428.8397 4818.916) (9434.2137 4822.0458)
      (9439.0534 4825.7252) (9442.6412 4828.5191) (9444.7786 4829.2214) (9445.8015 4827.2214) (9446.3664 4822.7023)
      (9447.1756 4816.687) (9448.7634 4810.6718) (9450.3817 4807.7405) (9450.3817 4840.8092)
    ))
    ; P2087 -- see feature_dimensions_mm.csv
    ("06_ORNAMENT" 0 (
      (9450.3817 4550.7328) (9450.3817 4573.0382)
    ))
    ; P2088 -- see feature_dimensions_mm.csv
    ("06_ORNAMENT" 0 (
      (9450.3817 4573.0382) (9449.6489 4572.8855) (9445.771 4570.3053) (9443.1908 4566.4427) (9442.2901 4561.8779)
      (9443.1908 4557.3282) (9445.771 4553.4656) (9449.6489 4550.8855) (9450.3817 4550.7328)
    ))
    ; P2089 -- see feature_dimensions_mm.csv
    ("06_ORNAMENT" 0 (
      (9450.3817 4573.0382) (9450.3817 4606.1069) (9448.7634 4603.1756) (9447.1756 4597.1603) (9446.3664 4591.145)
      (9445.8015 4586.626) (9444.7786 4584.626) (9442.6412 4585.3282) (9439.0534 4588.1221) (9434.2137 4591.7863)
      (9428.8397 4594.9313) (9424.0 4596.3206) (9420.7328 4595.3435) (9419.7557 4592.0916) (9421.1603 4587.2366)
      (9424.2901 4581.8626) (9427.9695 4577.0229) (9430.7634 4573.4351) (9431.4656 4571.2977) (9429.4504 4570.2901)
      (9424.9466 4569.7252) (9418.916 4568.9008) (9412.9008 4567.313) (9408.4885 4564.8855) (9406.8702 4561.8779)
      (9408.4885 4558.8855) (9412.9008 4556.4427) (9418.916 4554.8702) (9424.9466 4554.0458) (9429.4504 4553.4809)
      (9431.4656 4552.458) (9430.7634 4550.3206) (9427.9695 4546.7328) (9424.2901 4541.8931) (9421.1603 4536.5344)
      (9419.7557 4531.6794) (9420.7328 4528.4122) (9424.0 4527.4504) (9428.8397 4528.8397) (9434.2137 4531.9695)
      (9439.0534 4535.6489) (9442.6412 4538.4427) (9444.7786 4539.145) (9445.8015 4537.145) (9446.3664 4532.626)
      (9447.1756 4526.6107) (9448.7634 4520.5954) (9450.3817 4517.6641) (9450.3817 4550.7328)
    ))
    ; P2090 -- see feature_dimensions_mm.csv
    ("06_ORNAMENT" 0 (
      (9450.3817 4360.6412) (9435.8779 4344.3206) (9450.3817 4328.0153)
    ))
    ; P2091 -- see feature_dimensions_mm.csv
    ("06_ORNAMENT" 0 (
      (9450.3817 4260.6565) (9450.3817 4282.9618)
    ))
    ; P2092 -- see feature_dimensions_mm.csv
    ("06_ORNAMENT" 0 (
      (9450.3817 4282.9618) (9449.6489 4282.8092) (9445.771 4280.229) (9443.1908 4276.3664) (9442.2901 4271.8015)
      (9443.1908 4267.2519) (9445.771 4263.3893) (9449.6489 4260.8092) (9450.3817 4260.6565)
    ))
    ; P2093 -- see feature_dimensions_mm.csv
    ("06_ORNAMENT" 0 (
      (9450.3817 4282.9618) (9450.3817 4316.0305) (9448.7634 4313.0992) (9447.1756 4307.084) (9446.3664 4301.0687)
      (9445.8015 4296.5496) (9444.7786 4294.5496) (9442.6412 4295.2519) (9439.0534 4298.0458) (9434.2137 4301.7099)
      (9428.8397 4304.855) (9424.0 4306.2443) (9420.7328 4305.2672) (9419.7557 4302.0153) (9421.1603 4297.1603)
      (9424.2901 4291.7863) (9427.9695 4286.9466) (9430.7634 4283.3588) (9431.4656 4281.2214) (9429.4504 4280.2137)
      (9424.9466 4279.6489) (9418.916 4278.8244) (9412.9008 4277.2366) (9408.4885 4274.8092) (9406.8702 4271.8015)
      (9408.4885 4268.8092) (9412.9008 4266.3664) (9418.916 4264.7939) (9424.9466 4263.9695) (9429.4504 4263.4046)
      (9431.4656 4262.3817) (9430.7634 4260.2443) (9427.9695 4256.6565) (9424.2901 4251.8168) (9421.1603 4246.458)
      (9419.7557 4241.6031) (9420.7328 4238.3359) (9424.0 4237.374) (9428.8397 4238.7634) (9434.2137 4241.8931)
      (9439.0534 4245.5725) (9442.6412 4248.3664) (9444.7786 4249.0687) (9445.8015 4247.0687) (9446.3664 4242.5496)
      (9447.1756 4236.5344) (9448.7634 4230.5191) (9450.3817 4227.5878) (9450.3817 4260.6565)
    ))
    ; P2094 -- see feature_dimensions_mm.csv
    ("06_ORNAMENT" 0 (
      (9450.3817 4070.5649) (9435.8779 4054.2443) (9450.3817 4037.9389)
    ))
    ; P2095 -- see feature_dimensions_mm.csv
    ("06_ORNAMENT" 0 (
      (9450.3817 4025.9542) (9448.7634 4023.0229) (9447.1756 4017.0076) (9446.3664 4010.9924) (9445.8015 4006.4733)
      (9444.7786 4004.4733) (9442.6412 4005.1756) (9439.0534 4007.9695) (9434.2137 4011.6336) (9428.8397 4014.7786)
      (9424.0 4016.1679) (9420.7328 4015.1908) (9419.7557 4011.9389) (9421.1603 4007.084) (9424.2901 4001.7099)
      (9427.9695 3996.8702) (9430.7634 3993.2824) (9431.4656 3991.145) (9429.4504 3990.1374) (9424.9466 3989.5725)
      (9418.916 3988.7481) (9412.9008 3987.1603) (9408.4885 3984.7328) (9406.8702 3981.7252) (9408.4885 3978.7328)
      (9412.9008 3976.2901) (9418.916 3974.7176) (9424.9466 3973.8931) (9429.4504 3973.3282) (9431.4656 3972.3053)
      (9430.7634 3970.1679) (9427.9695 3966.5802) (9424.2901 3961.7405) (9421.1603 3956.3817) (9419.7557 3951.5267)
      (9420.7328 3948.2595) (9424.0 3947.2977) (9428.8397 3948.687) (9434.2137 3951.8168) (9439.0534 3955.4962)
      (9442.6412 3958.2901) (9444.7786 3958.9924) (9445.8015 3956.9924) (9446.3664 3952.4733) (9447.1756 3946.458)
      (9448.7634 3940.4427) (9450.3817 3937.5115) (9450.3817 3970.5802) (9449.6489 3970.7328) (9445.771 3973.313)
      (9443.1908 3977.1756) (9442.2901 3981.7252) (9443.1908 3986.2901) (9445.771 3990.1527) (9449.6489 3992.7328)
      (9450.3817 3992.8855)
    ))
    ; P2096 -- see feature_dimensions_mm.csv
    ("06_ORNAMENT" 0 (
      (9526.7176 5275.1603) (9531.2672 5276.0763) (9535.145 5278.6565) (9537.7252 5282.5191) (9538.626 5287.0687)
      (9537.7252 5291.6336) (9535.145 5295.4962) (9531.2672 5298.0763) (9526.7176 5298.9771)
    ))
    ; P2097 -- see feature_dimensions_mm.csv
    ("06_ORNAMENT" 0 (
      (9526.7176 5298.9771) (9526.7176 5275.1603)
    ))
    ; P2098 -- see feature_dimensions_mm.csv
    ("06_ORNAMENT" 0 (
      (9526.7176 5275.1603) (9526.7176 5239.7405) (9529.7099 5241.3588) (9532.1527 5245.7863) (9533.7405 5251.8015)
      (9534.5649 5257.8168) (9535.1145 5262.3359) (9536.1374 5264.3359) (9538.2748 5263.6336) (9541.8626 5260.8397)
      (9546.7023 5257.1603) (9552.0763 5254.0305) (9556.916 5252.6412) (9560.1832 5253.6031) (9561.1603 5256.8702)
      (9559.7557 5261.7252) (9556.626 5267.084) (9552.9466 5271.9237) (9550.1527 5275.5115) (9549.4504 5277.6489)
      (9551.4656 5278.6718) (9555.9695 5279.2366) (9562.0 5280.0611) (9568.0153 5281.6336) (9572.4275 5284.0763)
      (9574.0458 5287.0687) (9572.4275 5290.0763) (9568.0153 5292.5038) (9562.0 5294.0916) (9555.9695 5294.916)
      (9551.4656 5295.4809) (9549.4504 5296.4885) (9550.1527 5298.626) (9552.9466 5302.2137) (9556.626 5307.0534)
      (9559.7557 5312.4275) (9561.1603 5317.2824) (9560.1832 5320.5344) (9556.916 5321.5115) (9552.0763 5320.1221)
      (9546.7023 5316.9771) (9541.8626 5313.313) (9538.2748 5310.5191) (9536.1374 5309.8168) (9535.1145 5311.8168)
      (9534.5649 5316.3359) (9533.7405 5322.3511) (9532.1527 5328.3664) (9529.7099 5332.7786) (9526.7176 5334.3969)
      (9526.7176 5298.9771)
    ))
    ; P2099 -- see feature_dimensions_mm.csv
    ("06_ORNAMENT" 0 (
      (9526.7176 4985.084) (9531.2672 4986.0) (9535.145 4988.5802) (9537.7252 4992.4427) (9538.626 4996.9924)
      (9537.7252 5001.5573) (9535.145 5005.4198) (9531.2672 5008.0) (9526.7176 5008.9008)
    ))
    ; P2100 -- see feature_dimensions_mm.csv
    ("06_ORNAMENT" 0 (
      (9526.7176 5008.9008) (9526.7176 4985.084)
    ))
    ; P2101 -- see feature_dimensions_mm.csv
    ("06_ORNAMENT" 0 (
      (9526.7176 4985.084) (9526.7176 4949.6641) (9529.7099 4951.2824) (9532.1527 4955.7099) (9533.7405 4961.7252)
      (9534.5649 4967.7405) (9535.1145 4972.2595) (9536.1374 4974.2595) (9538.2748 4973.5573) (9541.8626 4970.7634)
      (9546.7023 4967.084) (9552.0763 4963.9542) (9556.916 4962.5649) (9560.1832 4963.5267) (9561.1603 4966.7939)
      (9559.7557 4971.6489) (9556.626 4977.0076) (9552.9466 4981.8473) (9550.1527 4985.4351) (9549.4504 4987.5725)
      (9551.4656 4988.5954) (9555.9695 4989.1603) (9562.0 4989.9847) (9568.0153 4991.5573) (9572.4275 4994.0)
      (9574.0458 4996.9924) (9572.4275 5000.0) (9568.0153 5002.4275) (9562.0 5004.0153) (9555.9695 5004.8397)
      (9551.4656 5005.4046) (9549.4504 5006.4122) (9550.1527 5008.5496) (9552.9466 5012.1374) (9556.626 5016.9771)
      (9559.7557 5022.3511) (9561.1603 5027.2061) (9560.1832 5030.458) (9556.916 5031.4351) (9552.0763 5030.0458)
      (9546.7023 5026.9008) (9541.8626 5023.2366) (9538.2748 5020.4427) (9536.1374 5019.7405) (9535.1145 5021.7405)
      (9534.5649 5026.2595) (9533.7405 5032.2748) (9532.1527 5038.2901) (9529.7099 5042.7023) (9526.7176 5044.3206)
      (9526.7176 5008.9008)
    ))
    ; P2102 -- see feature_dimensions_mm.csv
    ("06_ORNAMENT" 0 (
      (9526.7176 4695.0076) (9531.2672 4695.9237) (9535.145 4698.5038) (9537.7252 4702.3664) (9538.626 4706.916)
      (9537.7252 4711.4809) (9535.145 4715.3435) (9531.2672 4717.9237) (9526.7176 4718.8244)
    ))
    ; P2103 -- see feature_dimensions_mm.csv
    ("06_ORNAMENT" 0 (
      (9526.7176 4718.8244) (9526.7176 4695.0076)
    ))
    ; P2104 -- see feature_dimensions_mm.csv
    ("06_ORNAMENT" 0 (
      (9526.7176 4695.0076) (9526.7176 4659.5878) (9529.7099 4661.2061) (9532.1527 4665.6336) (9533.7405 4671.6489)
      (9534.5649 4677.6641) (9535.1145 4682.1832) (9536.1374 4684.1832) (9538.2748 4683.4809) (9541.8626 4680.687)
      (9546.7023 4677.0076) (9552.0763 4673.8779) (9556.916 4672.4885) (9560.1832 4673.4504) (9561.1603 4676.7176)
      (9559.7557 4681.5725) (9556.626 4686.9313) (9552.9466 4691.771) (9550.1527 4695.3588) (9549.4504 4697.4962)
      (9551.4656 4698.5191) (9555.9695 4699.084) (9562.0 4699.9084) (9568.0153 4701.4809) (9572.4275 4703.9237)
      (9574.0458 4706.916) (9572.4275 4709.9237) (9568.0153 4712.3511) (9562.0 4713.9389) (9555.9695 4714.7634)
      (9551.4656 4715.3282) (9549.4504 4716.3359) (9550.1527 4718.4733) (9552.9466 4722.0611) (9556.626 4726.9008)
      (9559.7557 4732.2748) (9561.1603 4737.1298) (9560.1832 4740.3817) (9556.916 4741.3588) (9552.0763 4739.9695)
      (9546.7023 4736.8244) (9541.8626 4733.1603) (9538.2748 4730.3664) (9536.1374 4729.6641) (9535.1145 4731.6641)
      (9534.5649 4736.1832) (9533.7405 4742.1985) (9532.1527 4748.2137) (9529.7099 4752.626) (9526.7176 4754.2443)
      (9526.7176 4718.8244)
    ))
    ; P2105 -- see feature_dimensions_mm.csv
    ("06_ORNAMENT" 0 (
      (9530.7481 4473.2824) (9545.0382 4489.3588) (9526.7176 4509.9695) (9526.7176 4473.2824)
    ))
    ; P2106 -- see feature_dimensions_mm.csv
    ("06_ORNAMENT" 0 (
      (9526.7176 4412.2137) (9526.7176 4404.9313)
    ))
    ; P2107 -- see feature_dimensions_mm.csv
    ("06_ORNAMENT" 0 (
      (9526.7176 4404.9313) (9526.7176 4369.5115) (9529.7099 4371.1298) (9532.1527 4375.5573) (9533.7405 4381.5725)
      (9534.5649 4387.5878) (9535.1145 4392.1069) (9536.1374 4394.1069) (9538.2748 4393.4046) (9541.8626 4390.6107)
      (9546.7023 4386.9313) (9552.0763 4383.8015) (9556.916 4382.4122) (9560.1832 4383.374) (9561.1603 4386.6412)
      (9559.7557 4391.4962) (9556.626 4396.855) (9552.9466 4401.6947) (9550.1527 4405.2824) (9549.4504 4407.4198)
      (9551.4656 4408.4427) (9555.9695 4409.0076) (9562.0 4409.8321) (9568.0153 4411.4046) (9569.4656 4412.2137)
    ))
    ; P2108 -- see feature_dimensions_mm.csv
    ("06_ORNAMENT" 0 (
      (9526.7176 4404.9313) (9531.2672 4405.8473) (9535.145 4408.4275) (9537.6641 4412.2137)
    ))
    ; P2109 -- see feature_dimensions_mm.csv
    ("06_ORNAMENT" 0 (
      (9526.7176 4114.855) (9531.2672 4115.771) (9535.145 4118.3511) (9537.7252 4122.2137) (9538.626 4126.7634)
      (9537.7252 4131.3282) (9535.145 4135.1908) (9531.2672 4137.771) (9526.7176 4138.6718)
    ))
    ; P2110 -- see feature_dimensions_mm.csv
    ("06_ORNAMENT" 0 (
      (9526.7176 4138.6718) (9526.7176 4114.855)
    ))
    ; P2111 -- see feature_dimensions_mm.csv
    ("06_ORNAMENT" 0 (
      (9526.7176 4114.855) (9526.7176 4079.4351) (9529.7099 4081.0534) (9532.1527 4085.4809) (9533.7405 4091.4962)
      (9534.5649 4097.5115) (9535.1145 4102.0305) (9536.1374 4104.0305) (9538.2748 4103.3282) (9541.8626 4100.5344)
      (9546.7023 4096.855) (9552.0763 4093.7252) (9556.916 4092.3359) (9560.1832 4093.2977) (9561.1603 4096.5649)
      (9559.7557 4101.4198) (9556.626 4106.7786) (9552.9466 4111.6183) (9550.1527 4115.2061) (9549.4504 4117.3435)
      (9551.4656 4118.3664) (9555.9695 4118.9313) (9562.0 4119.7557) (9568.0153 4121.3282) (9572.4275 4123.771)
      (9574.0458 4126.7634) (9572.4275 4129.771) (9568.0153 4132.1985) (9562.0 4133.7863) (9555.9695 4134.6107)
      (9551.4656 4135.1756) (9549.4504 4136.1832) (9550.1527 4138.3206) (9552.9466 4141.9084) (9556.626 4146.7481)
      (9559.7557 4152.1221) (9561.1603 4156.9771) (9560.1832 4160.229) (9556.916 4161.2061) (9552.0763 4159.8168)
      (9546.7023 4156.6718) (9541.8626 4153.0076) (9538.2748 4150.2137) (9536.1374 4149.5115) (9535.1145 4151.5115)
      (9534.5649 4156.0305) (9533.7405 4162.0458) (9532.1527 4168.0611) (9529.7099 4172.4733) (9526.7176 4174.0916)
      (9526.7176 4138.6718)
    ))
    ; P2112 -- see feature_dimensions_mm.csv
    ("06_ORNAMENT" 0 (
      (9537.6641 3832.0611) (9537.7252 3832.1374) (9538.626 3836.687) (9537.7252 3841.2519) (9535.145 3845.1145)
      (9531.2672 3847.6947) (9526.7176 3848.5954)
    ))
    ; P2113 -- see feature_dimensions_mm.csv
    ("06_ORNAMENT" 0 (
      (9526.7176 3848.5954) (9526.7176 3832.0611) (9537.6641 3832.0611)
    ))
    ; P2114 -- see feature_dimensions_mm.csv
    ("06_ORNAMENT" 0 (
      (9537.6641 3832.0611) (9569.4656 3832.0611) (9572.4275 3833.6947) (9574.0458 3836.687) (9572.4275 3839.6947)
      (9568.0153 3842.1221) (9562.0 3843.7099) (9555.9695 3844.5344) (9551.4656 3845.0992) (9549.4504 3846.1069)
      (9550.1527 3848.2443) (9552.9466 3851.8321) (9556.626 3856.6718) (9559.7557 3862.0458) (9561.1603 3866.9008)
      (9560.1832 3870.1527) (9556.916 3871.1298) (9552.0763 3869.7405) (9546.7023 3866.5954) (9541.8626 3862.9313)
      (9538.2748 3860.1374) (9536.1374 3859.4351) (9535.1145 3861.4351) (9534.5649 3865.9542) (9533.7405 3871.9695)
      (9532.1527 3877.9847) (9529.7099 3882.3969) (9526.7176 3884.0153) (9526.7176 3848.5954)
    ))
    ; P2115 -- see feature_dimensions_mm.csv
    ("06_ORNAMENT" 0 (
      (9641.8015 2811.3588) (9676.3053 2798.5191) (9689.9695 2793.0534) (9693.7252 2805.9847) (9703.8321 2847.4351)
      (9712.2901 2889.3282) (9719.084 2931.0534) (9724.2443 2972.0458) (9727.7252 3011.6947) (9729.5725 3049.4046)
      (9729.7557 3084.5954) (9729.2977 3094.8244) (9732.2443 3091.4351) (9737.1298 3085.0076) (9743.2061 3077.7863)
      (9750.2748 3071.145) (9757.7863 3066.3511) (9764.9618 3064.3817) (9770.9924 3065.7099) (9775.1603 3070.2595)
      (9777.0382 3077.4656) (9776.6412 3086.3664) (9774.4122 3095.8168) (9771.2061 3104.687) (9768.0916 3112.1221)
      (9766.1832 3117.6489) (9766.4427 3121.2214) (9769.4198 3123.2366) (9775.145 3124.3511) (9783.145 3125.3588)
      (9792.4427 3127.0229) (9801.7252 3129.8168) (9809.6336 3133.9237) (9814.9313 3139.1603) (9816.7939 3145.0382)
      (9814.9313 3150.916) (9809.6336 3156.1527) (9801.7252 3160.2595) (9792.4427 3163.0534) (9783.145 3164.7176)
      (9775.145 3165.7252) (9769.4198 3166.8397) (9766.4427 3168.855) (9766.1832 3172.4275) (9768.0916 3177.9542)
      (9771.2061 3185.3893) (9774.4122 3194.2595) (9776.6412 3203.7099) (9777.0382 3212.6107) (9775.1603 3219.8168)
      (9770.9924 3224.3664) (9764.9618 3225.6947) (9757.7863 3223.7252) (9750.2748 3218.9313) (9743.2061 3212.2901)
      (9737.1298 3205.0687) (9732.2443 3198.6412) (9728.4122 3194.2443) (9725.1908 3192.6718) (9721.9695 3194.2443)
      (9718.1374 3198.6412) (9713.2519 3205.0687) (9707.1756 3212.2901) (9700.1069 3218.9313) (9692.5954 3223.7252)
      (9685.4198 3225.6947) (9679.3893 3224.3664) (9675.2214 3219.8168) (9673.3435 3212.6107) (9673.7405 3203.7099)
      (9675.9695 3194.2595) (9679.1756 3185.3893) (9682.2901 3177.9542) (9684.1985 3172.4275) (9683.9389 3168.855)
      (9680.9618 3166.8397) (9675.2366 3165.7252) (9667.2366 3164.7176) (9657.9389 3163.0534) (9648.6565 3160.2595)
      (9640.7481 3156.1527) (9635.4504 3150.916) (9633.5878 3145.0382) (9635.4504 3139.1603) (9640.7481 3133.9237)
      (9648.6565 3129.8168) (9657.9389 3127.0229) (9667.2366 3125.3588) (9675.2366 3124.3511) (9680.9618 3123.2366)
      (9683.9389 3121.2214) (9684.1985 3117.6489) (9682.2901 3112.1221) (9679.1756 3104.687) (9675.9695 3095.8168)
      (9673.7405 3086.3664) (9673.3435 3077.4656) (9675.2214 3070.2595) (9679.3893 3065.7099) (9685.4198 3064.3817)
      (9687.374 3064.916) (9681.8931 3051.6031) (9668.4122 3014.916) (9655.7863 2976.2901) (9644.2443 2936.2443)
      (9634.0305 2895.2977) (9625.3435 2853.9389) (9619.4962 2819.0534)
    ))
    ; P2116 -- see feature_dimensions_mm.csv
    ("06_ORNAMENT" 0 (
      (9629.0076 4412.2137) (9630.458 4411.4046) (9636.4733 4409.8321) (9642.5038 4409.0076) (9647.0076 4408.4427)
      (9649.0229 4407.4198) (9648.3206 4405.2824) (9645.5267 4401.6947) (9641.8473 4396.855) (9638.7176 4391.4962)
      (9637.313 4386.6412) (9638.2901 4383.374) (9641.5573 4382.4122) (9646.3969 4383.8015) (9651.771 4386.9313)
      (9656.6107 4390.6107) (9660.1985 4393.4046) (9662.3359 4394.1069) (9663.3588 4392.1069) (9663.9237 4387.5878)
      (9664.7328 4381.5725) (9666.3206 4375.5573) (9668.7634 4371.1298) (9671.7557 4369.5115) (9674.7481 4371.1298)
      (9677.1908 4375.5573) (9678.7786 4381.5725) (9679.6031 4387.5878) (9680.1527 4392.1069) (9681.1756 4394.1069)
      (9683.313 4393.4046) (9686.9008 4390.6107) (9691.7405 4386.9313) (9697.1145 4383.8015) (9701.9542 4382.4122)
      (9705.2214 4383.374) (9706.1985 4386.6412) (9704.7939 4391.4962) (9701.6641 4396.855) (9697.9847 4401.6947)
      (9695.1908 4405.2824) (9694.4885 4407.4198) (9696.5038 4408.4427) (9701.0076 4409.0076) (9707.0382 4409.8321)
      (9713.0534 4411.4046) (9714.5038 4412.2137)
    ))
    ; P2117 -- see feature_dimensions_mm.csv
    ("06_ORNAMENT" 0 (
      (9660.8092 4412.2137) (9663.3282 4408.4275) (9667.2061 4405.8473) (9671.7557 4404.9313) (9676.3053 4405.8473)
      (9680.1832 4408.4275) (9682.7023 4412.2137)
    ))
    ; P2118 -- see feature_dimensions_mm.csv
    ("06_ORNAMENT" 0 (
      (9660.8092 3832.0611) (9682.7023 3832.0611)
    ))
    ; P2119 -- see feature_dimensions_mm.csv
    ("06_ORNAMENT" 0 (
      (9682.7023 3832.0611) (9714.5038 3832.0611) (9717.4656 3833.6947) (9719.084 3836.687) (9717.4656 3839.6947)
      (9713.0534 3842.1221) (9707.0382 3843.7099) (9701.0076 3844.5344) (9696.5038 3845.0992) (9694.4885 3846.1069)
      (9695.1908 3848.2443) (9697.9847 3851.8321) (9701.6641 3856.6718) (9704.7939 3862.0458) (9706.1985 3866.9008)
      (9705.2214 3870.1527) (9701.9542 3871.1298) (9697.1145 3869.7405) (9691.7405 3866.5954) (9686.9008 3862.9313)
      (9683.313 3860.1374) (9681.1756 3859.4351) (9680.1527 3861.4351) (9679.6031 3865.9542) (9678.7786 3871.9695)
      (9677.1908 3877.9847) (9674.7481 3882.3969) (9671.7557 3884.0153) (9668.7634 3882.3969) (9666.3206 3877.9847)
      (9664.7328 3871.9695) (9663.9237 3865.9542) (9663.3588 3861.4351) (9662.3359 3859.4351) (9660.1985 3860.1374)
      (9656.6107 3862.9313) (9651.771 3866.5954) (9646.3969 3869.7405) (9641.5573 3871.1298) (9638.2901 3870.1527)
      (9637.313 3866.9008) (9638.7176 3862.0458) (9641.8473 3856.6718) (9645.5267 3851.8321) (9648.3206 3848.2443)
      (9649.0229 3846.1069) (9647.0076 3845.0992) (9642.5038 3844.5344) (9636.4733 3843.7099) (9630.458 3842.1221)
      (9626.0458 3839.6947) (9624.4275 3836.687) (9626.0458 3833.6947) (9629.0076 3832.0611) (9660.8092 3832.0611)
    ))
    ; P2120 -- see feature_dimensions_mm.csv
    ("06_ORNAMENT" 0 (
      (9682.7023 3832.0611) (9682.7634 3832.1374) (9683.6641 3836.687) (9682.7634 3841.2519) (9680.1832 3845.1145)
      (9676.3053 3847.6947) (9671.7557 3848.5954) (9667.2061 3847.6947) (9663.3282 3845.1145) (9660.7481 3841.2519)
      (9659.8473 3836.687) (9660.7481 3832.1374) (9660.8092 3832.0611)
    ))
    ; P2121 -- see feature_dimensions_mm.csv
    ("06_ORNAMENT" 0 (
      (9675.7863 4473.2824) (9690.0763 4489.3588) (9671.7557 4509.9695) (9653.4351 4489.3588) (9667.7252 4473.2824)
    ))
    ; P2122 -- see feature_dimensions_mm.csv
    ("06_ORNAMENT" 0 (
      (9726.7328 5452.4122) (9711.2824 5457.3893) (9714.3664 5452.0916) (9718.0458 5447.2519) (9720.8397 5443.6641)
      (9721.542 5441.5267) (9719.5267 5440.5191) (9715.0229 5439.9542) (9708.9924 5439.1298) (9702.9771 5437.542)
      (9698.5649 5435.1145) (9696.9466 5432.1069) (9698.5649 5429.1145) (9702.9771 5426.6718) (9708.9924 5425.0992)
      (9715.0229 5424.2748) (9719.5267 5423.7099) (9721.542 5422.687) (9720.8397 5420.5496) (9718.0458 5416.9618)
      (9714.3664 5412.1221) (9711.2366 5406.7634) (9709.8321 5401.9084) (9710.8092 5398.6412) (9714.0763 5397.6794)
      (9718.916 5399.0687) (9724.2901 5402.1985) (9729.1298 5405.8779) (9732.7176 5408.6718) (9734.855 5409.374)
      (9735.8779 5407.374) (9736.4427 5402.855) (9737.2519 5396.8397) (9738.8397 5390.8244) (9741.2824 5386.3969)
      (9744.2748 5384.7786) (9747.2672 5386.3969) (9749.7099 5390.8244) (9751.2977 5396.8397) (9752.1221 5402.855)
      (9752.6718 5407.374) (9753.6947 5409.374) (9755.8321 5408.6718) (9759.4198 5405.8779) (9764.2595 5402.1985)
      (9769.6336 5399.0687) (9774.4733 5397.6794) (9777.7405 5398.6412) (9778.7176 5401.9084) (9777.313 5406.7634)
      (9774.1832 5412.1221) (9770.5038 5416.9618) (9767.7099 5420.5496) (9767.0076 5422.687) (9769.0229 5423.7099)
      (9773.5267 5424.2748) (9779.5573 5425.0992) (9785.5725 5426.6718) (9789.9847 5429.1145) (9790.0458 5429.2366)
      (9786.9618 5430.5038)
    ))
    ; P2123 -- see feature_dimensions_mm.csv
    ("06_ORNAMENT" 0 (
      (9774.0458 4412.2137) (9775.4962 4411.4046) (9781.5115 4409.8321) (9787.542 4409.0076) (9792.0458 4408.4427)
      (9794.0611 4407.4198) (9793.3588 4405.2824) (9790.5649 4401.6947) (9786.8855 4396.855) (9783.7557 4391.4962)
      (9782.3511 4386.6412) (9783.3282 4383.374) (9786.5954 4382.4122) (9791.4351 4383.8015) (9796.8092 4386.9313)
      (9801.6489 4390.6107) (9805.2366 4393.4046) (9807.374 4394.1069) (9808.3969 4392.1069) (9808.9618 4387.5878)
      (9809.771 4381.5725) (9811.3588 4375.5573) (9813.8015 4371.1298) (9816.7939 4369.5115) (9819.7863 4371.1298)
      (9822.229 4375.5573) (9823.8168 4381.5725) (9824.6412 4387.5878) (9825.1908 4392.1069) (9826.2137 4394.1069)
      (9828.3511 4393.4046) (9831.9389 4390.6107) (9836.7786 4386.9313) (9842.1527 4383.8015) (9846.9924 4382.4122)
      (9850.2595 4383.374) (9851.2366 4386.6412) (9849.8321 4391.4962) (9846.7023 4396.855) (9843.0229 4401.6947)
      (9840.229 4405.2824) (9839.5267 4407.4198) (9841.542 4408.4427) (9846.0458 4409.0076) (9852.0763 4409.8321)
      (9858.0916 4411.4046) (9859.542 4412.2137)
    ))
    ; P2124 -- see feature_dimensions_mm.csv
    ("06_ORNAMENT" 0 (
      (9805.8473 4412.2137) (9808.3664 4408.4275) (9812.2443 4405.8473) (9816.7939 4404.9313) (9821.3435 4405.8473)
      (9825.2214 4408.4275) (9827.7405 4412.2137)
    ))
    ; P2125 -- see feature_dimensions_mm.csv
    ("06_ORNAMENT" 0 (
      (9805.8473 3832.0611) (9827.7405 3832.0611)
    ))
    ; P2126 -- see feature_dimensions_mm.csv
    ("06_ORNAMENT" 0 (
      (9827.7405 3832.0611) (9859.542 3832.0611) (9862.5038 3833.6947) (9864.1221 3836.687) (9862.5038 3839.6947)
      (9858.0916 3842.1221) (9852.0763 3843.7099) (9846.0458 3844.5344) (9841.542 3845.0992) (9839.5267 3846.1069)
      (9840.229 3848.2443) (9843.0229 3851.8321) (9846.7023 3856.6718) (9849.8321 3862.0458) (9851.2366 3866.9008)
      (9850.2595 3870.1527) (9846.9924 3871.1298) (9842.1527 3869.7405) (9836.7786 3866.5954) (9831.9389 3862.9313)
      (9828.3511 3860.1374) (9826.2137 3859.4351) (9825.1908 3861.4351) (9824.6412 3865.9542) (9823.8168 3871.9695)
      (9822.229 3877.9847) (9819.7863 3882.3969) (9816.7939 3884.0153) (9813.8015 3882.3969) (9811.3588 3877.9847)
      (9809.771 3871.9695) (9808.9618 3865.9542) (9808.3969 3861.4351) (9807.374 3859.4351) (9805.2366 3860.1374)
      (9801.6489 3862.9313) (9796.8092 3866.5954) (9791.4351 3869.7405) (9786.5954 3871.1298) (9783.3282 3870.1527)
      (9782.3511 3866.9008) (9783.7557 3862.0458) (9786.8855 3856.6718) (9790.5649 3851.8321) (9793.3588 3848.2443)
      (9794.0611 3846.1069) (9792.0458 3845.0992) (9787.542 3844.5344) (9781.5115 3843.7099) (9775.4962 3842.1221)
      (9771.084 3839.6947) (9769.4656 3836.687) (9771.084 3833.6947) (9774.0458 3832.0611) (9805.8473 3832.0611)
    ))
    ; P2127 -- see feature_dimensions_mm.csv
    ("06_ORNAMENT" 0 (
      (9827.7405 3832.0611) (9827.8015 3832.1374) (9828.7023 3836.687) (9827.8015 3841.2519) (9825.2214 3845.1145)
      (9821.3435 3847.6947) (9816.7939 3848.5954) (9812.2443 3847.6947) (9808.3664 3845.1145) (9805.7863 3841.2519)
      (9804.8855 3836.687) (9805.7863 3832.1374) (9805.8473 3832.0611)
    ))
    ; P2128 -- see feature_dimensions_mm.csv
    ("06_ORNAMENT" 0 (
      (9820.8244 4473.2824) (9835.1145 4489.3588) (9816.7939 4509.9695) (9798.4733 4489.3588) (9812.7634 4473.2824)
    ))
    ; P2129 -- see feature_dimensions_mm.csv
    ("06_ORNAMENT" 0 (
      (9919.084 4412.2137) (9920.5344 4411.4046) (9926.5496 4409.8321) (9932.5802 4409.0076) (9937.084 4408.4427)
      (9939.0992 4407.4198) (9938.3969 4405.2824) (9935.6031 4401.6947) (9931.9237 4396.855) (9928.7939 4391.4962)
      (9927.3893 4386.6412) (9928.3664 4383.374) (9931.6336 4382.4122) (9936.4733 4383.8015) (9941.8473 4386.9313)
      (9946.687 4390.6107) (9950.2748 4393.4046) (9952.4122 4394.1069) (9953.4351 4392.1069) (9954.0 4387.5878)
      (9954.8092 4381.5725) (9956.3969 4375.5573) (9958.8397 4371.1298) (9961.8321 4369.5115) (9964.8244 4371.1298)
      (9967.2672 4375.5573) (9968.855 4381.5725) (9969.6794 4387.5878) (9970.229 4392.1069) (9971.2519 4394.1069)
      (9973.3893 4393.4046) (9976.9771 4390.6107) (9981.8168 4386.9313) (9987.1908 4383.8015) (9992.0305 4382.4122)
      (9995.2977 4383.374) (9996.2748 4386.6412) (9994.8702 4391.4962) (9991.7405 4396.855) (9988.0611 4401.6947)
      (9985.2672 4405.2824) (9984.5649 4407.4198) (9986.5802 4408.4427) (9991.084 4409.0076) (9997.1145 4409.8321)
      (10003.1298 4411.4046) (10004.5802 4412.2137)
    ))
    ; P2130 -- see feature_dimensions_mm.csv
    ("06_ORNAMENT" 0 (
      (10004.5802 3832.0611) (10007.542 3833.6947) (10009.1603 3836.687) (10007.542 3839.6947) (10003.1298 3842.1221)
      (9997.1145 3843.7099) (9991.084 3844.5344) (9986.5802 3845.0992) (9984.5649 3846.1069) (9985.2672 3848.2443)
      (9988.0611 3851.8321) (9991.7405 3856.6718) (9994.8702 3862.0458) (9996.2748 3866.9008) (9995.2977 3870.1527)
      (9992.0305 3871.1298) (9987.1908 3869.7405) (9981.8168 3866.5954) (9976.9771 3862.9313) (9973.3893 3860.1374)
      (9971.2519 3859.4351) (9970.229 3861.4351) (9969.6794 3865.9542) (9968.855 3871.9695) (9967.2672 3877.9847)
      (9964.8244 3882.3969) (9961.8321 3884.0153) (9958.8397 3882.3969) (9956.3969 3877.9847) (9954.8092 3871.9695)
      (9954.0 3865.9542) (9953.4351 3861.4351) (9952.4122 3859.4351) (9950.2748 3860.1374) (9946.687 3862.9313)
      (9941.8473 3866.5954) (9936.4733 3869.7405) (9931.6336 3871.1298) (9928.3664 3870.1527) (9927.3893 3866.9008)
      (9928.7939 3862.0458) (9931.9237 3856.6718) (9935.6031 3851.8321) (9938.3969 3848.2443) (9939.0992 3846.1069)
      (9937.084 3845.0992) (9932.5802 3844.5344) (9926.5496 3843.7099) (9920.5344 3842.1221) (9916.1221 3839.6947)
      (9914.5038 3836.687) (9916.1221 3833.6947) (9919.084 3832.0611)
    ))
    ; P2131 -- see feature_dimensions_mm.csv
    ("06_ORNAMENT" 0 (
      (9950.8855 4412.2137) (9953.4046 4408.4275) (9957.2824 4405.8473) (9961.8321 4404.9313) (9966.3817 4405.8473)
      (9970.2595 4408.4275) (9972.7786 4412.2137)
    ))
    ; P2132 -- see feature_dimensions_mm.csv
    ("06_ORNAMENT" 0 (
      (9965.8626 4473.2824) (9980.1527 4489.3588) (9961.8321 4509.9695) (9943.5115 4489.3588) (9957.8015 4473.2824)
    ))
    ; P2133 -- see feature_dimensions_mm.csv
    ("06_ORNAMENT" 0 (
      (9979.6336 5315.3282) (9976.9771 5313.313) (9973.3893 5310.5191) (9971.2519 5309.8168) (9970.229 5311.8168)
      (9969.6794 5316.3359) (9968.855 5322.3511) (9967.542 5327.3282) (9967.1908 5327.6641) (9960.1832 5333.5115)
      (9958.8397 5332.7786) (9956.3969 5328.3664) (9954.8092 5322.3511) (9954.0 5316.3359) (9953.4351 5311.8168)
      (9952.4122 5309.8168) (9950.2748 5310.5191) (9946.687 5313.313) (9941.8473 5316.9771) (9936.4733 5320.1221)
      (9931.6336 5321.5115) (9928.3664 5320.5344) (9927.3893 5317.2824) (9928.7939 5312.4275) (9931.9237 5307.0534)
      (9935.6031 5302.2137) (9938.3969 5298.626) (9939.0992 5296.4885) (9937.084 5295.4809) (9932.5802 5294.916)
      (9926.5496 5294.0916) (9920.5344 5292.5038) (9916.1221 5290.0763) (9914.5038 5287.0687) (9916.1221 5284.0763)
      (9920.5344 5281.6336) (9926.5496 5280.0611) (9932.5802 5279.2366) (9937.084 5278.6718) (9939.0992 5277.6489)
      (9938.3969 5275.5115) (9935.6031 5271.9237) (9931.9237 5267.084) (9928.7939 5261.7252) (9927.3893 5256.8702)
      (9928.3664 5253.6031) (9931.6336 5252.6412) (9936.4733 5254.0305) (9941.8473 5257.1603) (9946.687 5260.8397)
      (9950.2748 5263.6336) (9952.4122 5264.3359) (9953.4351 5262.3359) (9954.0 5257.8168) (9954.8092 5251.8015)
      (9956.3969 5245.7863) (9958.8397 5241.3588) (9961.8321 5239.7405) (9964.8244 5241.3588) (9967.2672 5245.7863)
      (9968.855 5251.8015) (9969.6794 5257.8168) (9970.229 5262.3359) (9971.2519 5264.3359) (9973.3893 5263.6336)
      (9976.9771 5260.8397) (9981.8168 5257.1603) (9987.1908 5254.0305) (9992.0305 5252.6412) (9995.2977 5253.6031)
      (9996.2748 5256.8702) (9994.8702 5261.7252) (9991.7405 5267.084) (9988.0611 5271.9237) (9985.2672 5275.5115)
      (9984.5649 5277.6489) (9986.5802 5278.6718) (9991.084 5279.2366) (9997.1145 5280.0611) (10003.1298 5281.6336)
      (10005.7252 5283.0687)
    ))
    ; P2134 -- see feature_dimensions_mm.csv
    ("06_ORNAMENT" 0 (
      (9998.3664 5293.7557) (9997.1145 5294.0916) (9991.084 5294.916) (9986.5802 5295.4809) (9984.5649 5296.4885)
      (9985.2672 5298.626) (9988.0611 5302.2137) (9989.6947 5304.3664) (9985.4046 5309.5878)
    ))
    ; P2135 -- see feature_dimensions_mm.csv
    ("06_ORNAMENT" 0 (
      (10028.5496 5228.5649) (10028.5344 5228.626) (10016.0305 5214.5496) (10030.5344 5198.2443)
    ))
    ; P2136 -- see feature_dimensions_mm.csv
    ("06_ORNAMENT" 0 (
      (10030.5344 5186.2595) (10028.916 5183.3282) (10027.3282 5177.313) (10026.5191 5171.2977) (10025.9542 5166.7786)
      (10024.9313 5164.7786) (10022.7939 5165.4809) (10019.2061 5168.2748) (10014.3664 5171.9389) (10008.9924 5175.084)
      (10004.1527 5176.4733) (10000.8855 5175.4962) (9999.9084 5172.2443) (10001.313 5167.3893) (10004.4427 5162.0153)
      (10008.1221 5157.1756) (10010.916 5153.5878) (10011.6183 5151.4504) (10009.6031 5150.4427) (10005.0992 5149.8779)
      (9999.0687 5149.0534) (9993.0534 5147.4656) (9988.6412 5145.0382) (9987.0229 5142.0305) (9988.6412 5139.0382)
      (9993.0534 5136.5954) (9999.0687 5135.0229) (10005.0992 5134.1985) (10009.6031 5133.6336) (10011.6183 5132.6107)
      (10010.916 5130.4733) (10008.1221 5126.8855) (10004.4427 5122.0458) (10001.313 5116.687) (9999.9084 5111.8321)
      (10000.8855 5108.5649) (10004.1527 5107.6031) (10008.9924 5108.9924) (10014.3664 5112.1221) (10019.2061 5115.8015)
      (10022.7939 5118.5954) (10024.9313 5119.2977) (10025.9542 5117.2977) (10026.5191 5112.7786) (10027.3282 5106.7634)
      (10028.916 5100.7481) (10030.5344 5097.8168)
    ))
    ; P2137 -- see feature_dimensions_mm.csv
    ("06_ORNAMENT" 0 (
      (10030.5344 5153.1908) (10029.8015 5153.0382) (10025.9237 5150.458) (10023.3435 5146.5954) (10022.4427 5142.0305)
      (10023.3435 5137.4809) (10025.9237 5133.6183) (10029.8015 5131.0382) (10030.5344 5130.8855)
    ))
    ; P2138 -- see feature_dimensions_mm.csv
    ("06_ORNAMENT" 0 (
      (10030.5344 4940.7939) (10016.0305 4924.4733) (10030.5344 4908.1679)
    ))
    ; P2139 -- see feature_dimensions_mm.csv
    ("06_ORNAMENT" 0 (
      (10030.5344 4896.1832) (10028.916 4893.2519) (10027.3282 4887.2366) (10026.5191 4881.2214) (10025.9542 4876.7023)
      (10024.9313 4874.7023) (10022.7939 4875.4046) (10019.2061 4878.1985) (10014.3664 4881.8626) (10008.9924 4885.0076)
      (10004.1527 4886.3969) (10000.8855 4885.4198) (9999.9084 4882.1679) (10001.313 4877.313) (10004.4427 4871.9389)
      (10008.1221 4867.0992) (10010.916 4863.5115) (10011.6183 4861.374) (10009.6031 4860.3664) (10005.0992 4859.8015)
      (9999.0687 4858.9771) (9993.0534 4857.3893) (9988.6412 4854.9618) (9987.0229 4851.9542) (9988.6412 4848.9618)
      (9993.0534 4846.5191) (9999.0687 4844.9466) (10005.0992 4844.1221) (10009.6031 4843.5573) (10011.6183 4842.5344)
      (10010.916 4840.3969) (10008.1221 4836.8092) (10004.4427 4831.9695) (10001.313 4826.6107) (9999.9084 4821.7557)
      (10000.8855 4818.4885) (10004.1527 4817.5267) (10008.9924 4818.916) (10014.3664 4822.0458) (10019.2061 4825.7252)
      (10022.7939 4828.5191) (10024.9313 4829.2214) (10025.9542 4827.2214) (10026.5191 4822.7023) (10027.3282 4816.687)
      (10028.916 4810.6718) (10030.5344 4807.7405)
    ))
    ; P2140 -- see feature_dimensions_mm.csv
    ("06_ORNAMENT" 0 (
      (10030.5344 4863.1145) (10029.8015 4862.9618) (10025.9237 4860.3817) (10023.3435 4856.5191) (10022.4427 4851.9542)
      (10023.3435 4847.4046) (10025.9237 4843.542) (10029.8015 4840.9618) (10030.5344 4840.8092)
    ))
    ; P2141 -- see feature_dimensions_mm.csv
    ("06_ORNAMENT" 0 (
      (10030.5344 4650.7176) (10016.0305 4634.3969) (10030.5344 4618.0916)
    ))
    ; P2142 -- see feature_dimensions_mm.csv
    ("06_ORNAMENT" 0 (
      (10030.5344 4606.1069) (10028.916 4603.1756) (10027.3282 4597.1603) (10026.5191 4591.145) (10025.9542 4586.626)
      (10024.9313 4584.626) (10022.7939 4585.3282) (10019.2061 4588.1221) (10014.3664 4591.7863) (10008.9924 4594.9313)
      (10004.1527 4596.3206) (10000.8855 4595.3435) (9999.9084 4592.0916) (10001.313 4587.2366) (10004.4427 4581.8626)
      (10008.1221 4577.0229) (10010.916 4573.4351) (10011.6183 4571.2977) (10009.6031 4570.2901) (10005.0992 4569.7252)
      (9999.0687 4568.9008) (9993.0534 4567.313) (9988.6412 4564.8855) (9987.0229 4561.8779) (9988.6412 4558.8855)
      (9993.0534 4556.4427) (9999.0687 4554.8702) (10005.0992 4554.0458) (10009.6031 4553.4809) (10011.6183 4552.458)
      (10010.916 4550.3206) (10008.1221 4546.7328) (10004.4427 4541.8931) (10001.313 4536.5344) (9999.9084 4531.6794)
      (10000.8855 4528.4122) (10004.1527 4527.4504) (10008.9924 4528.8397) (10014.3664 4531.9695) (10019.2061 4535.6489)
      (10022.7939 4538.4427) (10024.9313 4539.145) (10025.9542 4537.145) (10026.5191 4532.626) (10027.3282 4526.6107)
      (10028.916 4520.5954) (10030.5344 4517.6641)
    ))
    ; P2143 -- see feature_dimensions_mm.csv
    ("06_ORNAMENT" 0 (
      (10030.5344 4573.0382) (10029.8015 4572.8855) (10025.9237 4570.3053) (10023.3435 4566.4427) (10022.4427 4561.8779)
      (10023.3435 4557.3282) (10025.9237 4553.4656) (10029.8015 4550.8855) (10030.5344 4550.7328)
    ))
    ; P2144 -- see feature_dimensions_mm.csv
    ("06_ORNAMENT" 0 (
      (10030.5344 4260.6565) (10030.5344 4282.9618)
    ))
    ; P2145 -- see feature_dimensions_mm.csv
    ("06_ORNAMENT" 0 (
      (10030.5344 4282.9618) (10029.8015 4282.8092) (10025.9237 4280.229) (10023.3435 4276.3664) (10022.4427 4271.8015)
      (10023.3435 4267.2519) (10025.9237 4263.3893) (10029.8015 4260.8092) (10030.5344 4260.6565)
    ))
    ; P2146 -- see feature_dimensions_mm.csv
    ("06_ORNAMENT" 0 (
      (10030.5344 4282.9618) (10030.5344 4316.0305) (10028.916 4313.0992) (10027.3282 4307.084) (10026.5191 4301.0687)
      (10025.9542 4296.5496) (10024.9313 4294.5496) (10022.7939 4295.2519) (10019.2061 4298.0458) (10014.3664 4301.7099)
      (10008.9924 4304.855) (10004.1527 4306.2443) (10000.8855 4305.2672) (9999.9084 4302.0153) (10001.313 4297.1603)
      (10004.4427 4291.7863) (10008.1221 4286.9466) (10010.916 4283.3588) (10011.6183 4281.2214) (10009.6031 4280.2137)
      (10005.0992 4279.6489) (9999.0687 4278.8244) (9993.0534 4277.2366) (9988.6412 4274.8092) (9987.0229 4271.8015)
      (9988.6412 4268.8092) (9993.0534 4266.3664) (9999.0687 4264.7939) (10005.0992 4263.9695) (10009.6031 4263.4046)
      (10011.6183 4262.3817) (10010.916 4260.2443) (10008.1221 4256.6565) (10004.4427 4251.8168) (10001.313 4246.458)
      (9999.9084 4241.6031) (10000.8855 4238.3359) (10004.1527 4237.374) (10008.9924 4238.7634) (10014.3664 4241.8931)
      (10019.2061 4245.5725) (10022.7939 4248.3664) (10024.9313 4249.0687) (10025.9542 4247.0687) (10026.5191 4242.5496)
      (10027.3282 4236.5344) (10028.916 4230.5191) (10030.5344 4227.5878) (10030.5344 4260.6565)
    ))
    ; P2147 -- see feature_dimensions_mm.csv
    ("06_ORNAMENT" 0 (
      (10030.5344 3970.5802) (10030.5344 3992.8855)
    ))
    ; P2148 -- see feature_dimensions_mm.csv
    ("06_ORNAMENT" 0 (
      (10030.5344 3992.8855) (10029.8015 3992.7328) (10025.9237 3990.1527) (10023.3435 3986.2901) (10022.4427 3981.7252)
      (10023.3435 3977.1756) (10025.9237 3973.313) (10029.8015 3970.7328) (10030.5344 3970.5802)
    ))
    ; P2149 -- see feature_dimensions_mm.csv
    ("06_ORNAMENT" 0 (
      (10030.5344 3992.8855) (10030.5344 4025.9542) (10028.916 4023.0229) (10027.3282 4017.0076) (10026.5191 4010.9924)
      (10025.9542 4006.4733) (10024.9313 4004.4733) (10022.7939 4005.1756) (10019.2061 4007.9695) (10014.3664 4011.6336)
      (10008.9924 4014.7786) (10004.1527 4016.1679) (10000.8855 4015.1908) (9999.9084 4011.9389) (10001.313 4007.084)
      (10004.4427 4001.7099) (10008.1221 3996.8702) (10010.916 3993.2824) (10011.6183 3991.145) (10009.6031 3990.1374)
      (10005.0992 3989.5725) (9999.0687 3988.7481) (9993.0534 3987.1603) (9988.6412 3984.7328) (9987.0229 3981.7252)
      (9988.6412 3978.7328) (9993.0534 3976.2901) (9999.0687 3974.7176) (10005.0992 3973.8931) (10009.6031 3973.3282)
      (10011.6183 3972.3053) (10010.916 3970.1679) (10008.1221 3966.5802) (10004.4427 3961.7405) (10001.313 3956.3817)
      (9999.9084 3951.5267) (10000.8855 3948.2595) (10004.1527 3947.2977) (10008.9924 3948.687) (10014.3664 3951.8168)
      (10019.2061 3955.4962) (10022.7939 3958.2901) (10024.9313 3958.9924) (10025.9542 3956.9924) (10026.5191 3952.4733)
      (10027.3282 3946.458) (10028.916 3940.4427) (10030.5344 3937.5115) (10030.5344 3970.5802)
    ))
    ; P2150 -- see feature_dimensions_mm.csv
    ("06_ORNAMENT" 1 (
      (10687.0229 5297.7099) (10717.5573 5267.1756) (10793.8931 5343.5115) (10717.5573 5419.8473) (10687.0229 5389.313)
    ))
    ; P2151 -- see feature_dimensions_mm.csv
    ("06_ORNAMENT" 0 (
      (10687.0229 5297.7099) (10687.0229 4442.7481)
    ))
    ; P2152 -- see feature_dimensions_mm.csv
    ("06_ORNAMENT" 0 (
      (10687.0229 4290.0763) (10763.3588 4366.4122) (10687.0229 4442.7481)
    ))
    ; P2153 -- see feature_dimensions_mm.csv
    ("06_ORNAMENT" 0 (
      (10687.0229 4442.7481) (10687.0229 4290.0763)
    ))
    ; P2154 -- see feature_dimensions_mm.csv
    ("06_ORNAMENT" 0 (
      (10687.0229 4290.0763) (10687.0229 4084.4122)
    ))
    ; P2155 -- see feature_dimensions_mm.csv
    ("06_ORNAMENT" 0 (
      (11053.4351 4102.2443) (11043.8931 4095.3893) (11023.2672 4078.5802) (11002.6718 4059.8015) (10982.458 4039.2824)
      (10962.9313 4017.2977) (10944.4122 3994.0458) (10927.2214 3969.8168) (10920.2595 3958.5954) (10916.8702 3956.9466)
      (10898.7481 3947.2214) (10896.8244 3950.9466) (10912.1069 3971.9237) (10926.626 3993.7557) (10939.6947 4015.4046)
      (10951.1603 4036.5344) (10960.8702 4056.8092) (10968.6565 4075.8779) (10974.3511 4093.4046) (10957.1908 4082.6107)
      (10939.2061 4069.771) (10920.687 4055.0687) (10901.9084 4038.7481) (10883.1603 4020.9924) (10864.7328 4002.0153)
      (10861.771 3998.7023) (10853.5725 4007.0229) (10853.1145 4007.4351) (10855.1298 4014.458) (10861.2824 4039.9389)
      (10866.1374 4064.7481) (10869.6641 4088.5344) (10871.8321 4110.9008) (10872.5954 4131.4809) (10871.9389 4149.9084)
      (10859.5267 4133.8931) (10847.0382 4115.6489) (10834.6718 4095.4962) (10822.6412 4073.7252) (10811.1145 4050.6107)
      (10806.5802 4040.4733) (10805.4656 4041.0687) (10793.8931 4045.8015) (10795.542 4032.3511) (10798.0 4020.6412)
      (10790.4275 4001.6183) (10789.1603 3997.9542) (10788.9008 4008.1221) (10787.0229 4034.8702) (10784.0611 4060.916)
      (10780.1221 4085.8931) (10775.2672 4109.4351) (10769.6336 4131.1908) (10763.313 4150.7939) (10756.3817 4167.8626)
      (10750.1985 4148.5649) (10744.7176 4127.1603) (10740.0153 4103.9847) (10736.1832 4079.3893) (10733.2824 4053.7405)
      (10731.4046 4027.3588) (10730.6412 4000.6107) (10730.7176 3996.7481) (10726.9771 4006.2137) (10716.0458 4030.687)
      (10704.3359 4054.1374) (10692.0611 4076.2443) (10687.0229 4084.4122)
    ))
    ; P2156 -- see feature_dimensions_mm.csv
    ("06_ORNAMENT" 0 (
      (10687.0229 4084.4122) (10687.0229 3948.2595)
    ))
    ; P2157 -- see feature_dimensions_mm.csv
    ("06_ORNAMENT" 0 (
      (10687.0229 3948.2595) (10695.0992 3929.9084) (10706.8244 3906.7328) (10719.542 3885.0076) (10733.2366 3865.084)
      (10747.8626 3847.313) (10763.3588 3832.0611) (10786.1374 3835.3588) (10809.6489 3841.1145) (10833.6336 3849.0687)
      (10857.8015 3858.9618) (10878.7481 3868.9924) (10878.2901 3867.6336) (10872.626 3841.9847) (10870.229 3816.7939)
      (10893.9695 3828.9313) (10916.916 3844.1679) (10938.9618 3862.1221) (10959.9542 3882.3817) (10979.7863 3904.5344)
      (10998.3053 3928.1679) (11015.3893 3952.9008) (11030.9313 3978.2901) (11034.4122 3984.7481) (11039.8015 3990.7023)
      (11051.1756 4005.2061) (11044.687 4003.8168) (11044.7634 4003.9542) (11053.4351 4022.3969)
    ))
    ; P2158 -- see feature_dimensions_mm.csv
    ("06_ORNAMENT" 0 (
      (10687.0229 3948.2595) (10687.0229 3740.458) (10687.0229 3679.3893) (10687.0229 3664.1221) (10687.0229 3633.5878)
      (10717.5573 3633.5878) (11053.4351 3633.5878) (11053.4351 3679.3893) (11053.4351 3816.7939)
    ))
    ; P2159 -- see feature_dimensions_mm.csv
    ("06_ORNAMENT" 0 (
      (10900.7634 1609.5878) (10907.5573 1607.9084) (10918.8855 1606.1221) (10930.6565 1605.2214) (10942.687 1605.2366)
      (10954.8244 1606.2443) (10966.855 1608.2443) (10978.6412 1611.2824) (10990.0 1615.4046) (11000.7634 1620.6412)
      (11010.7481 1627.0382) (11019.7863 1634.626) (11027.7099 1643.4351) (11034.3511 1653.5267) (11022.9466 1658.7786)
      (11011.1298 1662.3053) (10999.0076 1664.229) (10986.7481 1664.6565) (10974.4885 1663.7252) (10962.3511 1661.5573)
      (10950.4885 1658.2595) (10939.0382 1653.9695) (10928.1527 1648.7939) (10917.9389 1642.8702) (10908.5802 1636.3053)
      (10900.7634 1629.7099)
    ))
    ; P2160 -- see feature_dimensions_mm.csv
    ("06_ORNAMENT" 0 (
      (11053.4351 4358.2748) (11053.4351 4438.1221)
    ))
    ; P2161 -- see feature_dimensions_mm.csv
    ("06_ORNAMENT" 0 (
      (11053.4351 4438.1221) (11043.8931 4431.2672) (11023.2672 4414.458) (11002.6718 4395.6794) (10982.458 4375.1603)
      (10962.9313 4353.1756) (10944.4122 4329.9237) (10927.2214 4305.6794) (10911.6947 4280.687) (10905.3282 4268.687)
      (10902.2901 4276.2137) (10894.6718 4291.0076) (10885.771 4305.1908) (10875.8321 4318.6565) (10865.0229 4331.2824)
      (10853.5725 4342.9008) (10841.6947 4353.4198) (10829.5725 4362.6718) (10817.4351 4370.5649) (10805.4656 4376.9466)
      (10793.8931 4381.6794) (10795.542 4368.229) (10798.5038 4354.0916) (10802.7023 4339.5115) (10808.0916 4324.7023)
      (10814.6107 4309.8931) (10822.229 4295.2977) (10830.8855 4281.1603) (10840.5191 4267.7099) (10851.0992 4255.145)
      (10862.5344 4243.7099) (10874.8092 4233.6183) (10885.9237 4226.3664) (10878.2901 4203.5115) (10872.626 4177.8626)
      (10870.229 4152.6718) (10893.9695 4164.8092) (10916.916 4180.0458) (10938.9618 4198.0) (10959.9542 4218.2595)
      (10979.7863 4240.4122) (10998.3053 4264.0458) (11015.3893 4288.7786) (11030.9313 4314.1679) (11044.7634 4339.8321)
      (11053.4351 4358.2748)
    ))
    ; P2162 -- see feature_dimensions_mm.csv
    ("06_ORNAMENT" 0 (
      (11053.4351 4438.1221) (11053.4351 4473.2824) (11129.771 4473.2824)
    ))
    ; P2163 -- see feature_dimensions_mm.csv
    ("06_ORNAMENT" 0 (
      (11053.4351 4152.6718) (11053.4351 4358.2748)
    ))
    ; P2164 -- see feature_dimensions_mm.csv
    ("06_ORNAMENT" 0 (
      (11053.4351 4102.2443) (11053.4351 4152.6718)
    ))
    ; P2165 -- see feature_dimensions_mm.csv
    ("06_ORNAMENT" 1 (
      (11053.4351 4152.6718) (11051.3588 4168.4733) (11045.2519 4183.2061) (11035.542 4195.8473) (11022.9008 4205.5573)
      (11008.1679 4211.6641) (10992.3664 4213.7405) (10976.5649 4211.6641) (10961.8321 4205.5573) (10949.1908 4195.8473)
      (10939.4809 4183.2061) (10933.374 4168.4733) (10931.2977 4152.6718) (10933.374 4136.8702) (10939.4809 4122.1374)
      (10949.1908 4109.4962) (10961.8321 4099.7863) (10976.5649 4093.6794) (10992.3664 4091.6031) (11008.1679 4093.6794)
      (11022.9008 4099.7863) (11035.542 4109.4962) (11045.2519 4122.1374) (11051.3588 4136.8702)
    ))
    ; P2166 -- see feature_dimensions_mm.csv
    ("06_ORNAMENT" 0 (
      (11053.4351 4022.3969) (11053.4351 4102.2443)
    ))
    ; P2167 -- see feature_dimensions_mm.csv
    ("06_ORNAMENT" 0 (
      (11053.4351 3816.7939) (11053.4351 4022.3969)
    ))
    ; P2168 -- see feature_dimensions_mm.csv
    ("06_ORNAMENT" 1 (
      (11053.4351 3816.7939) (11051.3588 3832.5954) (11045.2519 3847.3282) (11035.542 3859.9695) (11022.9008 3869.6794)
      (11008.1679 3875.7863) (10992.3664 3877.8626) (10976.5649 3875.7863) (10961.8321 3869.6794) (10949.1908 3859.9695)
      (10939.4809 3847.3282) (10933.374 3832.5954) (10931.2977 3816.7939) (10933.374 3800.9924) (10939.4809 3786.2595)
      (10949.1908 3773.6183) (10961.8321 3763.9084) (10976.5649 3757.8015) (10992.3664 3755.7252) (11008.1679 3757.8015)
      (11022.9008 3763.9084) (11035.542 3773.6183) (11045.2519 3786.2595) (11051.3588 3800.9924)
    ))
    ; P2169 -- see feature_dimensions_mm.csv
    ("06_ORNAMENT" 0 (
      (11114.5038 2839.6947) (11099.2366 2854.9618) (11083.9695 2839.6947)
    ))
    ; P2170 -- see feature_dimensions_mm.csv
    ("06_ORNAMENT" 0 (
      (11129.771 4412.2137) (11114.5038 4412.2137) (11114.5038 3832.0611) (11129.771 3832.0611)
    ))
    ; P2171 -- see feature_dimensions_mm.csv
    ("06_ORNAMENT" 0 (
      (11389.313 2839.6947) (11374.0458 2854.9618) (11358.7786 2839.6947)
    ))
    ; P2172 -- see feature_dimensions_mm.csv
    ("06_ORNAMENT" 0 (
      (11472.4122 4412.2137) (11474.6718 4409.3282) (11475.4046 4407.084) (11473.2977 4406.0153) (11468.5649 4405.4198)
      (11462.2443 4404.5649) (11455.9389 4402.9008) (11451.313 4400.3511) (11449.6183 4397.2061) (11451.313 4394.0611)
      (11455.9389 4391.5115) (11462.2443 4389.8473) (11468.5649 4388.9771) (11473.2977 4388.3969) (11475.4046 4387.3282)
      (11474.6718 4385.084) (11471.7405 4381.3282) (11467.8779 4376.2595) (11464.5954 4370.626) (11463.1298 4365.542)
      (11464.1527 4362.1221) (11467.5725 4361.0992) (11472.6565 4362.5649) (11478.2901 4365.8473) (11483.3588 4369.6947)
      (11487.1145 4372.626) (11489.3588 4373.3588) (11490.4275 4371.2672) (11491.0229 4366.5344) (11491.8779 4360.2137)
      (11493.542 4353.9084) (11496.0916 4349.2824) (11499.2366 4347.5878) (11502.3817 4349.2824) (11504.9313 4353.9084)
      (11506.5954 4360.2137) (11507.4504 4366.5344) (11508.0458 4371.2672) (11509.1145 4373.3588) (11511.3588 4372.626)
      (11515.1145 4369.6947) (11520.1832 4365.8473) (11525.8168 4362.5649) (11530.9008 4361.0992) (11534.3206 4362.1221)
      (11535.3435 4365.542) (11533.8779 4370.626) (11530.5954 4376.2595) (11526.7328 4381.3282) (11523.8015 4385.084)
      (11523.0687 4387.3282) (11525.1756 4388.3969) (11529.9084 4388.9771) (11536.229 4389.8473) (11542.5344 4391.5115)
      (11547.1603 4394.0611) (11548.855 4397.2061) (11547.1603 4400.3511) (11542.5344 4402.9008) (11536.229 4404.5649)
      (11529.9084 4405.4198) (11525.1756 4406.0153) (11523.0687 4407.084) (11523.8015 4409.3282) (11526.0611 4412.2137)
    ))
    ; P2173 -- see feature_dimensions_mm.csv
    ("06_ORNAMENT" 0 (
      (11515.9695 4473.2824) (11517.5573 4475.0687) (11499.2366 4495.6794) (11480.916 4475.0687) (11482.5038 4473.2824)
    ))
    ; P2174 -- see feature_dimensions_mm.csv
    ("06_ORNAMENT" 0 (
      (11499.6794 3832.0611) (11517.5573 3852.1679) (11499.2366 3872.7786) (11480.916 3852.1679) (11498.7939 3832.0611)
    ))
    ; P2175 -- see feature_dimensions_mm.csv
    ("06_ORNAMENT" 0 (
      (11628.1374 4412.2137) (11630.3969 4409.3282) (11631.1298 4407.084) (11629.0229 4406.0153) (11624.2901 4405.4198)
      (11617.9695 4404.5649) (11611.6641 4402.9008) (11607.0382 4400.3511) (11605.3435 4397.2061) (11607.0382 4394.0611)
      (11611.6641 4391.5115) (11617.9695 4389.8473) (11624.2901 4388.9771) (11629.0229 4388.3969) (11631.1298 4387.3282)
      (11630.3969 4385.084) (11627.4656 4381.3282) (11623.6031 4376.2595) (11620.3206 4370.626) (11618.855 4365.542)
      (11619.8779 4362.1221) (11623.2977 4361.0992) (11628.3817 4362.5649) (11634.0153 4365.8473) (11639.084 4369.6947)
      (11642.8397 4372.626) (11645.084 4373.3588) (11646.1527 4371.2672) (11646.7481 4366.5344) (11647.6031 4360.2137)
      (11649.2672 4353.9084) (11651.8168 4349.2824) (11654.9618 4347.5878) (11658.1069 4349.2824) (11660.6565 4353.9084)
      (11662.3206 4360.2137) (11663.1756 4366.5344) (11663.771 4371.2672) (11664.8397 4373.3588) (11667.084 4372.626)
      (11670.8397 4369.6947) (11675.9084 4365.8473) (11681.542 4362.5649) (11686.626 4361.0992) (11690.0458 4362.1221)
      (11691.0687 4365.542) (11689.6031 4370.626) (11686.3206 4376.2595) (11682.458 4381.3282) (11679.5267 4385.084)
      (11678.7939 4387.3282) (11680.9008 4388.3969) (11685.6336 4388.9771) (11691.9542 4389.8473) (11698.2595 4391.5115)
      (11702.8855 4394.0611) (11704.5802 4397.2061) (11702.8855 4400.3511) (11698.2595 4402.9008) (11691.9542 4404.5649)
      (11685.6336 4405.4198) (11680.9008 4406.0153) (11678.7939 4407.084) (11679.5267 4409.3282) (11681.7863 4412.2137)
    ))
    ; P2176 -- see feature_dimensions_mm.csv
    ("06_ORNAMENT" 0 (
      (11671.6947 4473.2824) (11673.2824 4475.0687) (11654.9618 4495.6794) (11636.6412 4475.0687) (11638.229 4473.2824)
    ))
    ; P2177 -- see feature_dimensions_mm.csv
    ("06_ORNAMENT" 0 (
      (11679.3893 2839.6947) (11664.1221 2854.9618) (11648.855 2839.6947)
    ))
    ; P2178 -- see feature_dimensions_mm.csv
    ("06_ORNAMENT" 0 (
      (11655.4046 3832.0611) (11673.2824 3852.1679) (11654.9618 3872.7786) (11636.6412 3852.1679) (11654.5191 3832.0611)
    ))
    ; P2179 -- see feature_dimensions_mm.csv
    ("06_ORNAMENT" 0 (
      (11687.4198 5482.7481) (11689.5267 5481.5878) (11695.8321 5479.9237) (11702.1527 5479.0534) (11706.8855 5478.4733)
      (11708.9924 5477.4046) (11708.2595 5475.1603) (11705.3282 5471.4046) (11701.4656 5466.3359) (11698.1832 5460.7023)
      (11696.7176 5455.6183) (11697.7405 5452.1985) (11701.1603 5451.1756) (11706.2443 5452.6412) (11711.8779 5455.9237)
      (11716.9466 5459.771) (11720.7023 5462.7023) (11722.9466 5463.4351) (11724.0153 5461.3435) (11724.6107 5456.6107)
      (11725.4656 5450.2901) (11727.1298 5443.9847) (11729.6794 5439.3588) (11732.8244 5437.6641) (11735.9695 5439.3588)
      (11738.5191 5443.9847) (11740.1832 5450.2901) (11741.0382 5456.6107) (11741.6336 5461.3435) (11742.7023 5463.4351)
      (11744.9466 5462.7023) (11748.7023 5459.771) (11753.771 5455.9237) (11759.4046 5452.6412) (11764.4885 5451.1756)
      (11767.9084 5452.1985) (11768.9313 5455.6183) (11767.4656 5460.7023) (11764.1832 5466.3359) (11760.3206 5471.4046)
      (11757.3893 5475.1603) (11756.6565 5477.4046) (11758.7634 5478.4733) (11763.4962 5479.0534) (11769.8168 5479.9237)
      (11776.1221 5481.5878) (11780.7481 5484.1374) (11782.4427 5487.2824) (11780.7481 5490.4275) (11776.1221 5492.9771)
      (11769.8168 5494.6412) (11763.4962 5495.4962) (11758.7634 5496.0916) (11756.6565 5497.1603) (11757.3893 5499.4046)
      (11760.3206 5503.1603) (11763.0382 5506.7176)
    ))
    ; P2180 -- see feature_dimensions_mm.csv
    ("06_ORNAMENT" 1 (
      (11735.9237 5498.5649) (11723.7557 5494.7176) (11721.8168 5491.8321) (11720.916 5487.2824) (11721.8168 5482.7176)
      (11724.3969 5478.855) (11728.2748 5476.2748) (11732.8244 5475.374) (11737.374 5476.2748) (11741.2519 5478.855)
      (11743.8321 5482.7176) (11744.7328 5487.2824) (11743.8321 5491.8321) (11741.2519 5495.6947) (11737.374 5498.2748)
    ))
    ; P2181 -- see feature_dimensions_mm.csv
    ("06_ORNAMENT" 0 (
      (11745.7405 5501.6641) (11735.9237 5498.5649)
    ))
    ; P2182 -- see feature_dimensions_mm.csv
    ("06_ORNAMENT" 0 (
      (11783.8626 4412.2137) (11786.1221 4409.3282) (11786.855 4407.084) (11784.7481 4406.0153) (11780.0153 4405.4198)
      (11773.6947 4404.5649) (11767.3893 4402.9008) (11762.7634 4400.3511) (11761.0687 4397.2061) (11762.7634 4394.0611)
      (11767.3893 4391.5115) (11773.6947 4389.8473) (11780.0153 4388.9771) (11784.7481 4388.3969) (11786.855 4387.3282)
      (11786.1221 4385.084) (11783.1908 4381.3282) (11779.3282 4376.2595) (11776.0458 4370.626) (11774.5802 4365.542)
      (11775.6031 4362.1221) (11779.0229 4361.0992) (11784.1069 4362.5649) (11789.7405 4365.8473) (11794.8092 4369.6947)
      (11798.5649 4372.626) (11800.8092 4373.3588) (11801.8779 4371.2672) (11802.4733 4366.5344) (11803.3282 4360.2137)
      (11804.9924 4353.9084) (11807.542 4349.2824) (11810.687 4347.5878) (11813.8321 4349.2824) (11816.3817 4353.9084)
      (11818.0458 4360.2137) (11818.9008 4366.5344) (11819.4962 4371.2672) (11820.5649 4373.3588) (11822.8092 4372.626)
      (11826.5649 4369.6947) (11831.6336 4365.8473) (11837.2672 4362.5649) (11842.3511 4361.0992) (11845.771 4362.1221)
      (11846.7939 4365.542) (11845.3282 4370.626) (11842.0458 4376.2595) (11838.1832 4381.3282) (11835.2519 4385.084)
      (11834.5191 4387.3282) (11836.626 4388.3969) (11841.3588 4388.9771) (11847.6794 4389.8473) (11853.9847 4391.5115)
      (11858.6107 4394.0611) (11860.3053 4397.2061) (11858.6107 4400.3511) (11853.9847 4402.9008) (11847.6794 4404.5649)
      (11841.3588 4405.4198) (11836.626 4406.0153) (11834.5191 4407.084) (11835.2519 4409.3282) (11837.5115 4412.2137)
    ))
    ; P2183 -- see feature_dimensions_mm.csv
    ("06_ORNAMENT" 0 (
      (11827.4198 4473.2824) (11829.0076 4475.0687) (11810.687 4495.6794) (11792.3664 4475.0687) (11793.9542 4473.2824)
    ))
    ; P2184 -- see feature_dimensions_mm.csv
    ("06_ORNAMENT" 0 (
      (11811.1298 3832.0611) (11829.0076 3852.1679) (11810.687 3872.7786) (11792.3664 3852.1679) (11810.2443 3832.0611)
    ))
    ; P2185 -- see feature_dimensions_mm.csv
    ("06_ORNAMENT" 0 (
      (11816.7939 1628.7023) (11815.8321 1629.6336) (11806.9008 1636.855) (11797.1603 1643.5267) (11786.7328 1649.5115)
      (11775.7252 1654.7176) (11764.3053 1659.0076) (11752.5802 1662.2595) (11740.6718 1664.3664) (11728.7328 1665.2214)
      (11716.8855 1664.6718) (11705.2672 1662.626) (11694.0 1658.9466) (11683.2061 1653.5267) (11690.458 1643.2824)
      (11698.9313 1634.3053) (11708.458 1626.5954) (11718.855 1620.0916) (11729.9542 1614.7634) (11741.542 1610.5802)
      (11753.4656 1607.4962) (11765.5267 1605.4962) (11777.542 1604.5191) (11789.3435 1604.5649) (11800.7481 1605.5573)
      (11811.5573 1607.4962) (11816.7939 1608.9618)
    ))
    ; P2186 -- see feature_dimensions_mm.csv
    ("06_ORNAMENT" 0 (
      (11939.5878 4412.2137) (11941.8473 4409.3282) (11942.5802 4407.084) (11940.4733 4406.0153) (11935.7405 4405.4198)
      (11929.4198 4404.5649) (11923.1145 4402.9008) (11918.4885 4400.3511) (11916.7939 4397.2061) (11918.4885 4394.0611)
      (11923.1145 4391.5115) (11929.4198 4389.8473) (11935.7405 4388.9771) (11940.4733 4388.3969) (11942.5802 4387.3282)
      (11941.8473 4385.084) (11938.916 4381.3282) (11935.0534 4376.2595) (11931.771 4370.626) (11930.3053 4365.542)
      (11931.3282 4362.1221) (11934.7481 4361.0992) (11939.8321 4362.5649) (11945.4656 4365.8473) (11950.5344 4369.6947)
      (11954.2901 4372.626) (11956.5344 4373.3588) (11957.6031 4371.2672) (11958.1985 4366.5344) (11959.0534 4360.2137)
      (11960.7176 4353.9084) (11963.2672 4349.2824) (11966.4122 4347.5878) (11969.5573 4349.2824) (11972.1069 4353.9084)
      (11973.771 4360.2137) (11974.626 4366.5344) (11975.2214 4371.2672) (11976.2901 4373.3588) (11978.5344 4372.626)
      (11982.2901 4369.6947) (11987.3588 4365.8473) (11992.9924 4362.5649) (11998.0763 4361.0992) (12001.4962 4362.1221)
      (12002.5191 4365.542) (12001.0534 4370.626) (11997.771 4376.2595) (11993.9084 4381.3282) (11990.9771 4385.084)
      (11990.2443 4387.3282) (11992.3511 4388.3969) (11997.084 4388.9771) (12003.4046 4389.8473) (12009.7099 4391.5115)
      (12014.3359 4394.0611) (12015.2672 4395.7863) (12015.2672 4398.6107) (12014.3359 4400.3511) (12009.7099 4402.9008)
      (12003.4046 4404.5649) (11997.084 4405.4198) (11992.3511 4406.0153) (11990.2443 4407.084) (11990.9771 4409.3282)
      (11993.2366 4412.2137)
    ))
    ; P2187 -- see feature_dimensions_mm.csv
    ("06_ORNAMENT" 0 (
      (11983.145 4473.2824) (11984.7328 4475.0687) (11966.4122 4495.6794) (11948.0916 4475.0687) (11949.6794 4473.2824)
    ))
    ; P2188 -- see feature_dimensions_mm.csv
    ("06_ORNAMENT" 0 (
      (11966.855 3832.0611) (11984.7328 3852.1679) (11966.4122 3872.7786) (11948.0916 3852.1679) (11965.9695 3832.0611)
    ))
    ; P2189 -- see feature_dimensions_mm.csv
    ("06_ORNAMENT" 0 (
      (12099.2366 4473.2824) (12106.8702 4473.2824)
    ))
    ; P2190 -- see feature_dimensions_mm.csv
    ("06_ORNAMENT" 0 (
      (12106.8702 4473.2824) (12138.8702 4473.2824)
    ))
    ; P2191 -- see feature_dimensions_mm.csv
    ("06_ORNAMENT" 0 (
      (12138.8702 4473.2824) (12140.458 4475.0687) (12122.1374 4495.6794) (12106.8702 4478.5038) (12106.8702 4473.2824)
    ))
    ; P2192 -- see feature_dimensions_mm.csv
    ("06_ORNAMENT" 0 (
      (12106.8702 4412.2137) (12106.8702 4370.1832) (12110.0153 4372.626) (12112.2595 4373.3588) (12113.3282 4371.2672)
      (12113.9237 4366.5344) (12114.7786 4360.2137) (12116.4427 4353.9084) (12118.9924 4349.2824) (12122.1374 4347.5878)
      (12125.2824 4349.2824) (12127.8321 4353.9084) (12129.4962 4360.2137) (12130.3511 4366.5344) (12130.9466 4371.2672)
      (12132.0153 4373.3588) (12134.2595 4372.626) (12138.0153 4369.6947) (12143.084 4365.8473) (12148.7176 4362.5649)
      (12153.8015 4361.0992) (12157.2214 4362.1221) (12158.2443 4365.542) (12156.7786 4370.626) (12153.4962 4376.2595)
      (12149.6336 4381.3282) (12146.7023 4385.084) (12145.9695 4387.3282) (12148.0763 4388.3969) (12152.8092 4388.9771)
      (12159.1298 4389.8473) (12165.4351 4391.5115) (12170.0611 4394.0611) (12171.7557 4397.2061) (12170.0611 4400.3511)
      (12165.4351 4402.9008) (12159.1298 4404.5649) (12152.8092 4405.4198) (12148.0763 4406.0153) (12145.9695 4407.084)
      (12146.7023 4409.3282) (12148.9618 4412.2137)
    ))
    ; P2193 -- see feature_dimensions_mm.csv
    ("06_ORNAMENT" 0 (
      (12122.5802 3832.0611) (12140.458 3852.1679) (12122.1374 3872.7786) (12106.8702 3855.6031) (12106.8702 3848.7328)
      (12121.6947 3832.0611)
    ))
    ; P2194 -- see feature_dimensions_mm.csv
    ("06_ORNAMENT" 0 (
      (12138.8702 4473.2824) (12261.1298 4473.2824)
    ))
    ; P2195 -- see feature_dimensions_mm.csv
    ("06_ORNAMENT" 0 (
      (12244.2748 1609.5878) (12251.0687 1607.9084) (12262.3969 1606.1221) (12274.1679 1605.2214) (12286.1985 1605.2366)
      (12298.3359 1606.2443) (12310.3664 1608.2443) (12322.1527 1611.2824) (12333.5115 1615.4046) (12344.2748 1620.6412)
      (12354.2595 1627.0382) (12363.2977 1634.626) (12371.2214 1643.4351) (12377.8626 1653.5267) (12366.458 1658.7786)
      (12354.6412 1662.3053) (12342.5191 1664.229) (12330.2595 1664.6565) (12318.0 1663.7252) (12305.8626 1661.5573)
      (12294.0 1658.2595) (12282.5496 1653.9695) (12271.6641 1648.7939) (12261.4504 1642.8702) (12252.0916 1636.3053)
      (12244.2748 1629.7099)
    ))
    ; P2196 -- see feature_dimensions_mm.csv
    ("06_ORNAMENT" 0 (
      (12251.0382 4412.2137) (12253.2977 4409.3282) (12254.0305 4407.084) (12251.9237 4406.0153) (12247.1908 4405.4198)
      (12240.8702 4404.5649) (12234.5649 4402.9008) (12229.9389 4400.3511) (12228.2443 4397.2061) (12229.9389 4394.0611)
      (12234.5649 4391.5115) (12240.8702 4389.8473) (12247.1908 4388.9771) (12251.9237 4388.3969) (12254.0305 4387.3282)
      (12253.2977 4385.084) (12250.3664 4381.3282) (12246.5038 4376.2595) (12243.2214 4370.626) (12241.7557 4365.542)
      (12242.7786 4362.1221) (12246.1985 4361.0992) (12251.2824 4362.5649) (12256.916 4365.8473) (12261.9847 4369.6947)
      (12265.7405 4372.626) (12267.9847 4373.3588) (12269.0534 4371.2672) (12269.6489 4366.5344) (12270.5038 4360.2137)
      (12272.1679 4353.9084) (12274.7176 4349.2824) (12277.8626 4347.5878) (12281.0076 4349.2824) (12283.5573 4353.9084)
      (12285.2214 4360.2137) (12286.0763 4366.5344) (12286.6718 4371.2672) (12287.7405 4373.3588) (12289.9847 4372.626)
      (12293.7405 4369.6947) (12298.8092 4365.8473) (12304.4427 4362.5649) (12309.5267 4361.0992) (12312.9466 4362.1221)
      (12313.9695 4365.542) (12312.5038 4370.626) (12309.2214 4376.2595) (12305.3588 4381.3282) (12302.4275 4385.084)
      (12301.6947 4387.3282) (12303.8015 4388.3969) (12308.5344 4388.9771) (12314.855 4389.8473) (12321.1603 4391.5115)
      (12325.7863 4394.0611) (12327.4809 4397.2061) (12325.7863 4400.3511) (12321.1603 4402.9008) (12314.855 4404.5649)
      (12308.5344 4405.4198) (12303.8015 4406.0153) (12301.6947 4407.084) (12302.4275 4409.3282) (12304.687 4412.2137)
    ))
    ; P2197 -- see feature_dimensions_mm.csv
    ("06_ORNAMENT" 0 (
      (12261.1298 4473.2824) (12294.5954 4473.2824)
    ))
    ; P2198 -- see feature_dimensions_mm.csv
    ("06_ORNAMENT" 0 (
      (12294.5954 4473.2824) (12296.1832 4475.0687) (12277.8626 4495.6794) (12259.542 4475.0687) (12261.1298 4473.2824)
    ))
    ; P2199 -- see feature_dimensions_mm.csv
    ("06_ORNAMENT" 0 (
      (12294.5954 4473.2824) (12416.855 4473.2824)
    ))
    ; P2200 -- see feature_dimensions_mm.csv
    ("06_ORNAMENT" 0 (
      (12336.3969 5513.3435) (12319.9542 5517.8015) (12321.084 5513.8626) (12324.3664 5508.229) (12328.229 5503.1603)
      (12331.1603 5499.4046) (12331.8931 5497.1603) (12329.7863 5496.0916) (12325.0534 5495.4962) (12318.7328 5494.6412)
      (12312.4275 5492.9771) (12307.8015 5490.4275) (12306.1069 5487.2824) (12307.8015 5484.1374) (12312.4275 5481.5878)
      (12318.7328 5479.9237) (12325.0534 5479.0534) (12329.7863 5478.4733) (12331.8931 5477.4046) (12331.1603 5475.1603)
      (12328.229 5471.4046) (12324.3664 5466.3359) (12321.084 5460.7023) (12319.6183 5455.6183) (12320.6412 5452.1985)
      (12324.0611 5451.1756) (12329.145 5452.6412) (12334.7786 5455.9237) (12339.8473 5459.771) (12343.6031 5462.7023)
      (12345.8473 5463.4351) (12346.916 5461.3435) (12347.5115 5456.6107) (12348.3664 5450.2901) (12350.0305 5443.9847)
      (12352.5802 5439.3588) (12355.7252 5437.6641) (12358.8702 5439.3588) (12361.4198 5443.9847) (12363.084 5450.2901)
      (12363.9389 5456.6107) (12364.5344 5461.3435) (12365.6031 5463.4351) (12367.8473 5462.7023) (12371.6031 5459.771)
      (12376.6718 5455.9237) (12382.3053 5452.6412) (12387.3893 5451.1756) (12390.8092 5452.1985) (12391.8321 5455.6183)
      (12390.3664 5460.7023) (12387.084 5466.3359) (12383.2214 5471.4046) (12380.2901 5475.1603) (12379.5573 5477.4046)
      (12381.6641 5478.4733) (12386.3969 5479.0534) (12392.7176 5479.9237) (12399.0229 5481.5878) (12403.6489 5484.1374)
      (12405.3435 5487.2824) (12403.6489 5490.4275) (12399.0229 5492.9771) (12392.7176 5494.6412) (12386.3969 5495.4962)
      (12381.6641 5496.0916) (12379.5573 5497.1603) (12380.2901 5499.4046) (12380.9466 5500.229) (12376.3969 5501.6641)
    ))
    ; P2201 -- see feature_dimensions_mm.csv
    ("06_ORNAMENT" 0 (
      (12406.7634 4412.2137) (12409.0229 4409.3282) (12409.7557 4407.084) (12407.6489 4406.0153) (12402.916 4405.4198)
      (12396.5954 4404.5649) (12390.2901 4402.9008) (12385.6641 4400.3511) (12383.9695 4397.2061) (12385.6641 4394.0611)
      (12390.2901 4391.5115) (12396.5954 4389.8473) (12402.916 4388.9771) (12407.6489 4388.3969) (12409.7557 4387.3282)
      (12409.0229 4385.084) (12406.0916 4381.3282) (12402.229 4376.2595) (12398.9466 4370.626) (12397.4809 4365.542)
      (12398.5038 4362.1221) (12401.9237 4361.0992) (12407.0076 4362.5649) (12412.6412 4365.8473) (12417.7099 4369.6947)
      (12421.4656 4372.626) (12423.7099 4373.3588) (12424.7786 4371.2672) (12425.374 4366.5344) (12426.229 4360.2137)
      (12427.8931 4353.9084) (12430.4427 4349.2824) (12433.5878 4347.5878) (12436.7328 4349.2824) (12439.2824 4353.9084)
      (12440.9466 4360.2137) (12441.8015 4366.5344) (12442.3969 4371.2672) (12443.4656 4373.3588) (12445.7099 4372.626)
      (12449.4656 4369.6947) (12454.5344 4365.8473) (12460.1679 4362.5649) (12465.2519 4361.0992) (12468.6718 4362.1221)
      (12469.6947 4365.542) (12468.229 4370.626) (12464.9466 4376.2595) (12461.084 4381.3282) (12458.1527 4385.084)
      (12457.4198 4387.3282) (12459.5267 4388.3969) (12464.2595 4388.9771) (12470.5802 4389.8473) (12476.8855 4391.5115)
      (12481.5115 4394.0611) (12483.2061 4397.2061) (12481.5115 4400.3511) (12476.8855 4402.9008) (12470.5802 4404.5649)
      (12464.2595 4405.4198) (12459.5267 4406.0153) (12457.4198 4407.084) (12458.1527 4409.3282) (12460.4122 4412.2137)
    ))
    ; P2202 -- see feature_dimensions_mm.csv
    ("06_ORNAMENT" 0 (
      (12416.855 4473.2824) (12450.3206 4473.2824)
    ))
    ; P2203 -- see feature_dimensions_mm.csv
    ("06_ORNAMENT" 0 (
      (12450.3206 4473.2824) (12451.9084 4475.0687) (12433.5878 4495.6794) (12415.2672 4475.0687) (12416.855 4473.2824)
    ))
    ; P2204 -- see feature_dimensions_mm.csv
    ("06_ORNAMENT" 0 (
      (12450.3206 4473.2824) (12572.5802 4473.2824)
    ))
    ; P2205 -- see feature_dimensions_mm.csv
    ("06_ORNAMENT" 0 (
      (12488.5496 2839.6947) (12473.2824 2854.9618) (12458.0153 2839.6947)
    ))
    ; P2206 -- see feature_dimensions_mm.csv
    ("06_ORNAMENT" 0 (
      (12495.1908 5460.7634) (12480.1527 5466.3969) (12480.0916 5466.3359) (12476.8092 5460.7023) (12475.3435 5455.6183)
      (12476.3664 5452.1985) (12479.7863 5451.1756) (12484.8702 5452.6412) (12490.5038 5455.9237) (12495.5725 5459.771)
      (12496.2748 5460.3206)
    ))
    ; P2207 -- see feature_dimensions_mm.csv
    ("06_ORNAMENT" 0 (
      (12503.1145 5457.5115) (12503.2366 5456.6107) (12504.0916 5450.2901) (12505.7557 5443.9847) (12508.3053 5439.3588)
      (12511.4504 5437.6641) (12514.5954 5439.3588) (12517.145 5443.9847) (12518.8092 5450.2901) (12518.9008 5451.0229)
    ))
    ; P2208 -- see feature_dimensions_mm.csv
    ("06_ORNAMENT" 0 (
      (12562.4885 4412.2137) (12564.7481 4409.3282) (12565.4809 4407.084) (12563.374 4406.0153) (12558.6412 4405.4198)
      (12552.3206 4404.5649) (12546.0153 4402.9008) (12541.3893 4400.3511) (12539.6947 4397.2061) (12541.3893 4394.0611)
      (12546.0153 4391.5115) (12552.3206 4389.8473) (12558.6412 4388.9771) (12563.374 4388.3969) (12565.4809 4387.3282)
      (12564.7481 4385.084) (12561.8168 4381.3282) (12557.9542 4376.2595) (12554.6718 4370.626) (12553.2061 4365.542)
      (12554.229 4362.1221) (12557.6489 4361.0992) (12562.7328 4362.5649) (12568.3664 4365.8473) (12573.4351 4369.6947)
      (12577.1908 4372.626) (12579.4351 4373.3588) (12580.5038 4371.2672) (12581.0992 4366.5344) (12581.9542 4360.2137)
      (12583.6183 4353.9084) (12586.1679 4349.2824) (12589.313 4347.5878) (12592.458 4349.2824) (12595.0076 4353.9084)
      (12596.6718 4360.2137) (12597.5267 4366.5344) (12598.1221 4371.2672) (12599.1908 4373.3588) (12601.4351 4372.626)
      (12605.1908 4369.6947) (12610.2595 4365.8473) (12615.8931 4362.5649) (12620.9771 4361.0992) (12624.3969 4362.1221)
      (12625.4198 4365.542) (12623.9542 4370.626) (12620.6718 4376.2595) (12616.8092 4381.3282) (12613.8779 4385.084)
      (12613.145 4387.3282) (12615.2519 4388.3969) (12619.9847 4388.9771) (12626.3053 4389.8473) (12632.6107 4391.5115)
      (12637.2366 4394.0611) (12638.9313 4397.2061) (12637.2366 4400.3511) (12632.6107 4402.9008) (12626.3053 4404.5649)
      (12619.9847 4405.4198) (12615.2519 4406.0153) (12613.145 4407.084) (12613.8779 4409.3282) (12616.1374 4412.2137)
      (12718.2137 4412.2137)
    ))
    ; P2209 -- see feature_dimensions_mm.csv
    ("06_ORNAMENT" 0 (
      (12572.5802 4473.2824) (12606.0458 4473.2824)
    ))
    ; P2210 -- see feature_dimensions_mm.csv
    ("06_ORNAMENT" 0 (
      (12606.0458 4473.2824) (12607.6336 4475.0687) (12589.313 4495.6794) (12570.9924 4475.0687) (12572.5802 4473.2824)
    ))
    ; P2211 -- see feature_dimensions_mm.csv
    ("06_ORNAMENT" 0 (
      (12606.0458 4473.2824) (12728.3053 4473.2824)
    ))
    ; P2212 -- see feature_dimensions_mm.csv
    ("06_ORNAMENT" 0 (
      (12709.1298 5339.0534) (12708.0458 5338.916) (12701.7405 5337.2519) (12697.1145 5334.7023) (12695.4198 5331.5573)
      (12697.1145 5328.4122) (12701.7405 5325.8626) (12708.0458 5324.1985) (12714.3664 5323.3282) (12719.0992 5322.7481)
      (12721.2061 5321.6794) (12720.4733 5319.4351) (12717.542 5315.6794) (12713.6794 5310.6107) (12710.3969 5304.9771)
      (12708.9313 5299.8931) (12709.9542 5296.4733) (12713.374 5295.4504) (12718.458 5296.916) (12724.0916 5300.1985)
      (12729.1603 5304.0458) (12732.916 5306.9771) (12735.1603 5307.7099) (12736.229 5305.6183) (12736.8244 5300.8855)
      (12737.6794 5294.5649) (12739.3435 5288.2595) (12741.8931 5283.6336) (12745.0382 5281.9389) (12748.1832 5283.6336)
      (12750.7328 5288.2595) (12751.3282 5290.5038)
    ))
    ; P2213 -- see feature_dimensions_mm.csv
    ("06_ORNAMENT" 0 (
      (12771.8626 4412.2137) (12718.2137 4412.2137)
    ))
    ; P2214 -- see feature_dimensions_mm.csv
    ("06_ORNAMENT" 0 (
      (12718.2137 4412.2137) (12720.4733 4409.3282) (12721.2061 4407.084) (12719.0992 4406.0153) (12714.3664 4405.4198)
      (12708.0458 4404.5649) (12701.7405 4402.9008) (12697.1145 4400.3511) (12695.4198 4397.2061) (12697.1145 4394.0611)
      (12701.7405 4391.5115) (12708.0458 4389.8473) (12714.3664 4388.9771) (12719.0992 4388.3969) (12721.2061 4387.3282)
      (12720.4733 4385.084) (12717.542 4381.3282) (12713.6794 4376.2595) (12710.3969 4370.626) (12708.9313 4365.542)
      (12709.9542 4362.1221) (12713.374 4361.0992) (12718.458 4362.5649) (12724.0916 4365.8473) (12729.1603 4369.6947)
      (12732.916 4372.626) (12735.1603 4373.3588) (12736.229 4371.2672) (12736.8244 4366.5344) (12737.6794 4360.2137)
      (12739.3435 4353.9084) (12741.8931 4349.2824) (12745.0382 4347.5878) (12748.1832 4349.2824) (12750.7328 4353.9084)
      (12752.3969 4360.2137) (12753.2519 4366.5344) (12753.8473 4371.2672) (12754.916 4373.3588) (12757.1603 4372.626)
      (12760.916 4369.6947) (12765.9847 4365.8473) (12771.6183 4362.5649) (12776.7023 4361.0992) (12778.626 4361.6641)
    ))
    ; P2215 -- see feature_dimensions_mm.csv
    ("06_ORNAMENT" 0 (
      (12728.3053 4473.2824) (12761.771 4473.2824)
    ))
    ; P2216 -- see feature_dimensions_mm.csv
    ("06_ORNAMENT" 0 (
      (12761.771 4473.2824) (12763.3588 4475.0687) (12745.0382 4495.6794) (12726.7176 4475.0687) (12728.3053 4473.2824)
    ))
    ; P2217 -- see feature_dimensions_mm.csv
    ("06_ORNAMENT" 0 (
      (13068.7023 4360.8244) (13068.916 4360.2901) (13081.2672 4334.2748) (13095.2519 4308.3969) (13110.7481 4283.0534)
      (13127.6489 4258.5954) (13145.8321 4235.4504) (13165.1756 4213.9847) (13185.5725 4194.5954) (13206.9008 4177.6489)
      (13229.0534 4163.542) (13251.9084 4152.6718) (13248.626 4179.1298) (13242.1679 4205.9084) (13235.0687 4226.3359)
      (13235.2519 4226.4427) (13248.7023 4235.4962) (13261.313 4246.0611) (13273.0229 4257.8626) (13283.7863 4270.7023)
      (13293.542 4284.3206) (13302.2137 4298.4733) (13309.7405 4312.9466) (13316.0763 4327.4962) (13321.1603 4341.8779)
      (13324.916 4355.8626) (13327.2977 4369.2061) (13328.2443 4381.6794) (13315.9542 4375.9542) (13303.4198 4368.7939)
      (13290.8397 4360.3206) (13278.4122 4350.626) (13266.3359 4339.8473) (13254.8092 4328.1069) (13244.0153 4315.5115)
      (13234.1832 4302.1985) (13225.4809 4288.2748) (13218.1374 4273.8626) (13216.0763 4268.626) (13206.9618 4285.6336)
      (13191.0992 4311.1298) (13173.7099 4335.6489) (13155.1756 4358.9466) (13135.7863 4380.7176) (13115.9084 4400.7481)
      (13095.8626 4418.7481) (13076.0153 4434.4733) (13068.7023 4439.4504) (13068.7023 4473.2824) (12992.3664 4473.2824)
      (12885.4962 4473.2824) (12778.626 4473.2824) (12761.771 4473.2824)
    ))
    ; P2218 -- see feature_dimensions_mm.csv
    ("06_ORNAMENT" 0 (
      (12992.3664 3832.0611) (13007.6336 3832.0611) (13007.6336 4412.2137) (12992.3664 4412.2137) (12885.4962 4412.2137)
      (12839.6947 4412.2137) (12809.1603 4412.2137) (12778.626 4412.2137) (12771.8626 4412.2137)
    ))
    ; P2219 -- see feature_dimensions_mm.csv
    ("06_ORNAMENT" 0 (
      (12778.626 4405.0229) (12775.7099 4405.4198) (12770.9771 4406.0153) (12768.8702 4407.084) (12769.6031 4409.3282)
      (12771.8626 4412.2137)
    ))
    ; P2220 -- see feature_dimensions_mm.csv
    ("06_ORNAMENT" 0 (
      (12778.626 4869.542) (12774.9771 4867.5267) (12773.2824 4864.3817) (12774.9771 4861.2366) (12778.626 4859.2214)
    ))
    ; P2221 -- see feature_dimensions_mm.csv
    ("06_ORNAMENT" 0 (
      (12778.626 4372.4275) (12776.3969 4376.2595) (12772.5344 4381.3282) (12769.6031 4385.084) (12768.8702 4387.3282)
      (12770.9771 4388.3969) (12775.7099 4388.9771) (12778.626 4389.3893)
    ))
    ; P2222 -- see feature_dimensions_mm.csv
    ("06_ORNAMENT" 0 (
      (12778.626 4246.6412) (12774.9771 4244.626) (12773.2824 4241.4809) (12774.9771 4238.3359) (12778.626 4236.3206)
    ))
    ; P2223 -- see feature_dimensions_mm.csv
    ("06_ORNAMENT" 0 (
      (12778.626 4121.2824) (12776.7023 4121.8626) (12771.6183 4120.3969) (12765.9847 4117.1145) (12760.916 4113.2519)
      (12757.1603 4110.3206) (12754.916 4109.5878) (12753.8473 4111.6947) (12753.2519 4116.4275) (12752.3969 4122.7328)
      (12750.7328 4129.0382) (12748.1832 4133.6794) (12745.0382 4135.374) (12741.8931 4133.6794) (12739.3435 4129.0382)
      (12737.6794 4122.7328) (12736.8244 4116.4275) (12736.229 4111.6947) (12735.1603 4109.5878) (12732.916 4110.3206)
      (12729.1603 4113.2519) (12724.0916 4117.1145) (12718.458 4120.3969) (12713.374 4121.8626) (12709.9542 4120.8397)
      (12708.9313 4117.4198) (12710.3969 4112.3359) (12713.6794 4106.7023) (12717.542 4101.6336) (12720.4733 4097.8779)
      (12721.2061 4095.6336) (12719.0992 4094.5649) (12714.3664 4093.9695) (12708.0458 4093.1145) (12701.7405 4091.4504)
      (12697.1145 4088.9008) (12695.4198 4085.7557) (12697.1145 4082.6107) (12701.7405 4080.0611) (12708.0458 4078.3969)
      (12714.3664 4077.5267) (12719.0992 4076.9466) (12721.2061 4075.8779) (12720.4733 4073.6336) (12717.542 4069.8779)
      (12713.6794 4064.8092) (12710.3969 4059.1756) (12708.9313 4054.0916) (12709.9542 4050.6718) (12713.374 4049.6489)
      (12718.458 4051.1145) (12724.0916 4054.3969) (12729.1603 4058.2595) (12732.916 4061.1756) (12735.1603 4061.9084)
      (12736.229 4059.8168) (12736.8244 4055.084) (12737.6794 4048.7634) (12739.3435 4042.458) (12741.8931 4037.8321)
      (12745.0382 4036.1374) (12748.1832 4037.8321) (12750.7328 4042.458) (12752.3969 4048.7634) (12753.2519 4055.084)
      (12753.8473 4059.8168) (12754.916 4061.9084) (12757.1603 4061.1756) (12760.916 4058.2595) (12765.9847 4054.3969)
      (12771.6183 4051.1145) (12776.7023 4049.6489) (12778.626 4050.2137)
    ))
    ; P2224 -- see feature_dimensions_mm.csv
    ("06_ORNAMENT" 0 (
      (12778.626 4093.5725) (12775.7099 4093.9695) (12770.9771 4094.5649) (12768.8702 4095.6336) (12769.6031 4097.8779)
      (12772.5344 4101.6336) (12776.3969 4106.7023) (12778.626 4110.5344)
    ))
    ; P2225 -- see feature_dimensions_mm.csv
    ("06_ORNAMENT" 0 (
      (12778.626 4060.9771) (12776.3969 4064.8092) (12772.5344 4069.8779) (12769.6031 4073.6336) (12768.8702 4075.8779)
      (12770.9771 4076.9466) (12775.7099 4077.5267) (12778.626 4077.9389)
    ))
    ; P2226 -- see feature_dimensions_mm.csv
    ("06_ORNAMENT" 0 (
      (13068.7023 4024.9466) (13068.916 4024.4122) (13078.687 4003.8321) (13070.9618 4005.2061) (13084.0 3989.6947)
      (13088.5954 3984.8397) (13095.2519 3972.5191) (13110.7481 3947.1756) (13127.6489 3922.7176) (13145.8321 3899.5725)
      (13165.1756 3878.1069) (13185.5725 3858.7176) (13206.9008 3841.771) (13229.0534 3827.6641) (13251.9084 3816.7939)
      (13248.626 3843.2519) (13242.3969 3869.0534) (13244.916 3867.6947) (13268.3664 3856.5344) (13291.7252 3847.1298)
      (13314.7481 3839.7557) (13337.1756 3834.6412) (13358.7786 3832.0611) (13374.7786 3848.6107) (13389.8626 3867.5573)
      (13403.9542 3888.5191) (13417.0229 3911.1145) (13429.0229 3934.9924) (13435.1145 3948.8855)
    ))
    ; P2227 -- see feature_dimensions_mm.csv
    ("06_ORNAMENT" 0 (
      (13068.7023 4024.9466) (13068.7023 3816.7939)
    ))
    ; P2228 -- see feature_dimensions_mm.csv
    ("06_ORNAMENT" 0 (
      (13435.1145 4082.6565) (13428.0458 4071.0382) (13415.5878 4048.4427) (13403.7863 4024.7786) (13392.8702 4000.3359)
      (13391.4504 3996.7481) (13391.6183 4006.916) (13390.855 4033.7099) (13388.9924 4059.8473) (13386.0763 4084.9771)
      (13382.2137 4108.7023) (13377.4962 4130.6718) (13371.9847 4150.5191) (13365.7557 4167.8626) (13358.7939 4148.8397)
      (13352.4275 4127.6794) (13346.7634 4104.7176) (13341.9084 4080.3053) (13337.9389 4054.7939) (13334.9771 4028.5191)
      (13333.0992 4001.8321) (13333.0076 3997.9542) (13329.6794 4007.5725) (13324.855 4019.7099) (13324.916 4019.9847)
      (13327.2977 4033.3282) (13328.2443 4045.8015) (13316.2901 4040.2443) (13309.0382 4056.3969) (13297.6947 4079.0076)
      (13285.9389 4099.9695) (13273.9542 4118.9924) (13261.9847 4135.7405) (13250.1985 4149.9084) (13250.1679 4129.6336)
      (13251.4504 4107.5725) (13254.0 4084.0611) (13257.8015 4059.4809) (13262.8244 4034.1527) (13269.0534 4008.458)
      (13269.5267 4006.8092) (13266.3359 4003.9695) (13260.9618 3998.4885) (13253.4046 4006.9618) (13235.1298 4025.7405)
      (13216.7328 4043.084) (13198.4885 4058.7481) (13180.7176 4072.5038) (13163.7099 4084.1374) (13147.7863 4093.4046)
      (13154.7176 4074.3511) (13163.4809 4054.0611) (13173.9389 4032.855) (13185.9389 4011.0687) (13199.3588 3988.9924)
      (13214.0153 3966.9924) (13225.145 3951.7252) (13223.0992 3947.7405) (13200.7634 3959.7252) (13191.0992 3975.2519)
      (13173.7099 3999.771) (13155.1756 4023.0687) (13135.7863 4044.8397) (13115.9084 4064.8702) (13095.8626 4082.8702)
      (13076.0153 4098.5954) (13068.7023 4103.5725) (13068.7023 4024.9466)
    ))
    ; P2229 -- see feature_dimensions_mm.csv
    ("06_ORNAMENT" 1 (
      (13068.7023 3816.7939) (13070.7786 3800.9924) (13076.8855 3786.2595) (13086.5954 3773.6183) (13099.2366 3763.9084)
      (13113.9695 3757.8015) (13129.771 3755.7252) (13145.5725 3757.8015) (13160.3053 3763.9084) (13172.9466 3773.6183)
      (13182.6565 3786.2595) (13188.7634 3800.9924) (13190.8397 3816.7939) (13188.7634 3832.5954) (13182.6565 3847.3282)
      (13172.9466 3859.9695) (13160.3053 3869.6794) (13145.5725 3875.7863) (13129.771 3877.8626) (13113.9695 3875.7863)
      (13099.2366 3869.6794) (13086.5954 3859.9695) (13076.8855 3847.3282) (13070.7786 3832.5954)
    ))
    ; P2230 -- see feature_dimensions_mm.csv
    ("06_ORNAMENT" 0 (
      (13068.7023 3816.7939) (13068.7023 3679.3893) (13068.7023 3633.5878) (13404.5802 3633.5878)
    ))
    ; P2231 -- see feature_dimensions_mm.csv
    ("06_ORNAMENT" 0 (
      (13435.1145 5389.313) (13435.1145 5465.6489) (13435.1145 5969.4656)
    ))
    ; P2232 -- see feature_dimensions_mm.csv
    ("06_ORNAMENT" 0 (
      (13435.1145 5297.7099) (13435.1145 5389.313)
    ))
    ; P2233 -- see feature_dimensions_mm.csv
    ("06_ORNAMENT" 0 (
      (13435.1145 5389.313) (13404.5802 5419.8473) (13328.2443 5343.5115) (13404.5802 5267.1756) (13435.1145 5297.7099)
    ))
    ; P2234 -- see feature_dimensions_mm.csv
    ("06_ORNAMENT" 0 (
      (13435.1145 4442.7481) (13435.1145 5297.7099)
    ))
    ; P2235 -- see feature_dimensions_mm.csv
    ("06_ORNAMENT" 0 (
      (13435.1145 4290.0763) (13435.1145 4442.7481)
    ))
    ; P2236 -- see feature_dimensions_mm.csv
    ("06_ORNAMENT" 0 (
      (13435.1145 4442.7481) (13358.7786 4366.4122) (13435.1145 4290.0763)
    ))
    ; P2237 -- see feature_dimensions_mm.csv
    ("06_ORNAMENT" 0 (
      (13435.1145 4082.6565) (13435.1145 4290.0763)
    ))
    ; P2238 -- see feature_dimensions_mm.csv
    ("06_ORNAMENT" 0 (
      (13435.1145 3948.8855) (13435.1145 4082.6565)
    ))
    ; P2239 -- see feature_dimensions_mm.csv
    ("06_ORNAMENT" 0 (
      (13435.1145 3664.1221) (13435.1145 3679.3893) (13435.1145 3740.458) (13435.1145 3948.8855)
    ))
    ; P2240 -- see feature_dimensions_mm.csv
    ("06_ORNAMENT" 1 (
      (1236.6412 7374.0458) (1297.7099 7343.5115) (1358.7786 7374.0458) (1297.7099 7404.5802)
    ))
    ; P2241 -- see feature_dimensions_mm.csv
    ("06_ORNAMENT" 1 (
      (1236.6412 7282.4427) (1297.7099 7251.9084) (1358.7786 7282.4427) (1297.7099 7312.9771)
    ))
    ; P2242 -- see feature_dimensions_mm.csv
    ("06_ORNAMENT" 1 (
      (1236.6412 7190.8397) (1297.7099 7160.3053) (1358.7786 7190.8397) (1297.7099 7221.374)
    ))
    ; P2243 -- see feature_dimensions_mm.csv
    ("06_ORNAMENT" 1 (
      (1465.6489 5725.1908) (1467.2977 5711.7405) (1470.2595 5697.6031) (1474.458 5683.0229) (1479.8473 5668.2137)
      (1486.3664 5653.4046) (1493.9847 5638.8092) (1502.6412 5624.6718) (1512.2748 5611.2214) (1522.855 5598.6565)
      (1534.2901 5587.2214) (1546.5649 5577.1298) (1557.6794 5569.8779) (1550.0458 5547.0229) (1544.3817 5521.374)
      (1541.9847 5496.1832) (1565.7252 5508.3206) (1588.6718 5523.5573) (1610.7176 5541.5115) (1631.7099 5561.771)
      (1651.542 5583.9237) (1670.0611 5607.5573) (1687.145 5632.2901) (1702.687 5657.6794) (1716.5191 5683.3435)
      (1728.5191 5708.8855) (1738.5802 5733.8779) (1746.5496 5757.9084) (1752.3053 5780.5954) (1755.7252 5801.5267)
      (1735.9847 5789.374) (1715.6489 5774.7786) (1695.0229 5757.9695) (1674.4275 5739.1908) (1654.2137 5718.6718)
      (1634.687 5696.687) (1616.1679 5673.4351) (1598.9771 5649.1908) (1583.4504 5624.1985) (1577.084 5612.1985)
      (1574.0458 5619.7252) (1566.4275 5634.5191) (1557.5267 5648.7023) (1547.5878 5662.1679) (1536.7786 5674.7939)
      (1525.3282 5686.4122) (1513.4504 5696.9313) (1501.3282 5706.1832) (1489.1908 5714.0763) (1477.2214 5720.458)
    ))
    ; P2244 -- see feature_dimensions_mm.csv
    ("06_ORNAMENT" 1 (
      (1465.6489 5389.313) (1467.2977 5375.8626) (1470.2595 5361.7252) (1474.458 5347.145) (1479.8473 5332.3359)
      (1486.3664 5317.5267) (1493.9847 5302.9313) (1502.6412 5288.7939) (1512.2748 5275.3435) (1522.855 5262.7786)
      (1534.2901 5251.3435) (1546.5649 5241.2519) (1557.6794 5234.0) (1550.0458 5211.145) (1544.3817 5185.4962)
      (1541.9847 5160.3053) (1565.7252 5172.4427) (1588.6718 5187.6794) (1610.7176 5205.6336) (1631.7099 5225.8931)
      (1651.542 5248.0458) (1670.0611 5271.6794) (1687.145 5296.4122) (1702.687 5321.8015) (1716.5191 5347.4656)
      (1728.5191 5373.0076) (1738.5802 5398.0) (1746.5496 5422.0305) (1752.3053 5444.7176) (1755.7252 5465.6489)
      (1735.9847 5453.4962) (1715.6489 5438.9008) (1695.0229 5422.0916) (1674.4275 5403.313) (1662.3664 5391.0687)
      (1633.5878 5419.8473) (1557.2519 5343.5115) (1594.5649 5306.1985) (1583.4504 5288.3206) (1577.084 5276.3206)
      (1574.0458 5283.8473) (1566.4275 5298.6412) (1557.5267 5312.8244) (1547.5878 5326.2901) (1536.7786 5338.916)
      (1525.3282 5350.5344) (1513.4504 5361.0534) (1501.3282 5370.3053) (1489.1908 5378.1985) (1477.2214 5384.5802)
    ))
    ; P2245 -- see feature_dimensions_mm.csv
    ("06_ORNAMENT" 1 (
      (1465.6489 5053.4351) (1467.2977 5039.9847) (1470.2595 5025.8473) (1474.458 5011.2672) (1479.8473 4996.458)
      (1486.3664 4981.6489) (1493.9847 4967.0534) (1502.6412 4952.916) (1512.2748 4939.4656) (1522.855 4926.9008)
      (1534.2901 4915.4656) (1546.5649 4905.374) (1557.6794 4898.1221) (1550.0458 4875.2672) (1544.3817 4849.6183)
      (1541.9847 4824.4275) (1565.7252 4836.5649) (1588.6718 4851.8015) (1610.7176 4869.7557) (1623.5115 4882.1069)
      (1625.8626 4871.3893) (1620.9466 4867.6031) (1611.2366 4854.9618) (1605.1298 4840.229) (1603.0534 4824.4275)
      (1605.1298 4808.626) (1611.2366 4793.8931) (1620.9466 4781.2519) (1633.5878 4771.542) (1648.3206 4765.4351)
      (1664.1221 4763.3588) (1674.7634 4764.7634) (1686.8397 4749.7863) (1690.4427 4746.1679) (1674.4275 4731.5573)
      (1654.2137 4711.0382) (1634.687 4689.0534) (1616.1679 4665.8015) (1598.9771 4641.5573) (1583.4504 4616.5649)
      (1577.084 4604.5649) (1574.0458 4612.0916) (1566.4275 4626.8855) (1557.5267 4641.0687) (1547.5878 4654.5344)
      (1536.7786 4667.1603) (1525.3282 4678.7786) (1513.4504 4689.2977) (1501.3282 4698.5496) (1489.1908 4706.4427)
      (1477.2214 4712.8244) (1465.6489 4717.5573) (1467.2977 4704.1069) (1470.2595 4689.9695) (1474.458 4675.3893)
      (1479.8473 4660.5802) (1486.3664 4645.771) (1493.9847 4631.1756) (1502.6412 4617.0382) (1512.2748 4603.5878)
      (1522.855 4591.0229) (1534.2901 4579.5878) (1546.5649 4569.4962) (1557.6794 4562.2443) (1550.0458 4539.3893)
      (1544.3817 4513.7405) (1541.9847 4488.5496) (1565.7252 4500.687) (1588.6718 4515.9237) (1610.7176 4533.8779)
      (1631.7099 4554.1374) (1651.542 4576.2901) (1670.0611 4599.9237) (1687.145 4624.6565) (1702.687 4650.0458)
      (1716.5191 4675.7099) (1728.5191 4701.2519) (1733.0534 4712.5191) (1736.4733 4710.458) (1755.7252 4702.2901)
      (1775.542 4711.4504) (1793.9847 4723.2214) (1810.9924 4737.2519) (1826.5344 4753.2061) (1840.5649 4770.7786)
      (1853.0687 4789.6183) (1864.0 4809.4046) (1873.2977 4829.8015) (1880.9618 4850.4885) (1886.9313 4871.1145)
      (1891.1603 4891.374) (1893.6336 4910.916) (1894.3053 4929.4198) (1893.1298 4946.5649) (1877.0687 4937.2366)
      (1860.9618 4925.9237) (1845.0534 4912.7786) (1829.5878 4898.0305) (1814.8397 4881.8168) (1801.0382 4864.3664)
      (1788.4733 4845.8626) (1777.3588 4826.4733) (1767.9695 4806.3969) (1760.5496 4785.8321) (1755.374 4764.9466)
      (1755.1603 4763.3893) (1754.5496 4767.6794) (1752.6412 4775.0229) (1755.7252 4793.8931) (1748.8244 4789.6489)
      (1741.2519 4810.3664) (1731.6489 4830.8397) (1720.4122 4850.4427) (1707.8168 4868.9924) (1694.1069 4886.2748)
      (1679.5725 4902.0763) (1664.4733 4916.229) (1658.458 4920.9924) (1670.0611 4935.8015) (1687.145 4960.5344)
      (1702.687 4985.9237) (1706.1374 4992.3359) (1708.9924 4986.8855) (1720.8702 4968.9313) (1734.5344 4952.7481)
      (1749.9847 4938.6107) (1767.2824 4926.855) (1788.5038 4931.9695) (1808.8855 4939.9084) (1828.3053 4950.3511)
      (1846.6565 4962.9771) (1863.8626 4977.4656) (1879.7863 4993.5115) (1894.3664 5010.7786) (1907.4809 5028.9771)
      (1919.0229 5047.771) (1928.9008 5066.8397) (1937.0076 5085.8779) (1943.2366 5104.5649) (1947.5115 5122.5802)
      (1949.6947 5139.6183) (1932.1374 5133.6183) (1914.1221 5125.6489) (1895.9542 5115.8779) (1877.9084 5104.4122)
      (1860.2748 5091.4046) (1843.3435 5076.9771) (1827.4046 5061.2672) (1812.7176 5044.4275) (1799.6031 5026.5649)
      (1788.3053 5007.8321) (1779.145 4988.3664) (1778.6565 4986.8855) (1778.8855 4991.2061) (1777.6183 5013.4504)
      (1774.1679 5035.6641) (1768.7328 5057.6183) (1761.542 5079.0382) (1752.8092 5099.6947) (1750.916 5103.3588)
      (1752.3053 5108.8397) (1755.7252 5129.771) (1741.6489 5121.1145) (1731.5725 5137.6641) (1723.6641 5148.687)
      (1725.1908 5160.3053) (1723.1145 5176.1069) (1717.0076 5190.8397) (1707.2977 5203.4809) (1694.6565 5213.1908)
      (1679.9237 5219.2977) (1664.1221 5221.374) (1648.3206 5219.2977) (1633.5878 5213.1908) (1620.9466 5203.4809)
      (1611.2366 5190.8397) (1605.1298 5176.1069) (1603.0534 5160.3053) (1605.1298 5144.5038) (1611.2366 5129.771)
      (1620.9466 5117.1298) (1633.5878 5107.4198) (1648.3206 5101.313) (1664.1221 5099.2366) (1674.1527 5100.5649)
      (1674.9466 5091.7863) (1678.3053 5070.9618) (1674.4275 5067.4351) (1654.2137 5046.916) (1634.687 5024.9313)
      (1616.1679 5001.6794) (1598.9771 4977.4351) (1583.4504 4952.4427) (1577.084 4940.4427) (1574.0458 4947.9695)
      (1566.4275 4962.7634) (1557.5267 4976.9466) (1547.5878 4990.4122) (1536.7786 5003.0382) (1525.3282 5014.6565)
      (1513.4504 5025.1756) (1501.3282 5034.4275) (1489.1908 5042.3206) (1477.2214 5048.7023)
    ))
    ; P2246 -- see feature_dimensions_mm.csv
    ("06_ORNAMENT" 1 (
      (1465.6489 4381.6794) (1467.2977 4368.229) (1470.2595 4354.0916) (1474.458 4339.5115) (1479.8473 4324.7023)
      (1486.3664 4309.8931) (1493.9847 4295.2977) (1502.6412 4281.1603) (1512.2748 4267.7099) (1522.855 4255.145)
      (1534.2901 4243.7099) (1546.5649 4233.6183) (1557.6794 4226.3664) (1550.0458 4203.5115) (1544.3817 4177.8626)
      (1541.9847 4152.6718) (1565.7252 4164.8092) (1588.6718 4180.0458) (1610.7176 4198.0) (1631.7099 4218.2595)
      (1651.542 4240.4122) (1670.0611 4264.0458) (1687.145 4288.7786) (1702.687 4314.1679) (1716.5191 4339.8321)
      (1728.5191 4365.374) (1738.5802 4390.3664) (1746.5496 4414.3969) (1752.3053 4437.084) (1755.7252 4458.0153)
      (1735.9847 4445.8626) (1715.6489 4431.2672) (1695.0229 4414.458) (1674.4275 4395.6794) (1662.3664 4383.4351)
      (1603.0534 4442.7481) (1526.7176 4366.4122) (1594.5649 4298.5649) (1583.4504 4280.687) (1577.084 4268.687)
      (1574.0458 4276.2137) (1566.4275 4291.0076) (1557.5267 4305.1908) (1547.5878 4318.6565) (1536.7786 4331.2824)
      (1525.3282 4342.9008) (1513.4504 4353.4198) (1501.3282 4362.6718) (1489.1908 4370.5649) (1477.2214 4376.9466)
    ))
    ; P2247 -- see feature_dimensions_mm.csv
    ("06_ORNAMENT" 1 (
      (1465.6489 4045.8015) (1467.2977 4032.3511) (1470.2595 4018.2137) (1474.458 4003.6336) (1479.8473 3988.8244)
      (1486.3664 3974.0153) (1493.9847 3959.4198) (1502.6412 3945.2824) (1512.2748 3931.8321) (1522.855 3919.2672)
      (1534.2901 3907.8321) (1546.5649 3897.7405) (1557.6794 3890.4885) (1550.0458 3867.6336) (1544.3817 3841.9847)
      (1541.9847 3816.7939) (1565.7252 3828.9313) (1588.6718 3844.1679) (1610.7176 3862.1221) (1631.7099 3882.3817)
      (1634.9771 3886.0305) (1635.5725 3885.0076) (1643.3435 3873.7252) (1633.5878 3869.6794) (1620.9466 3859.9695)
      (1611.2366 3847.3282) (1605.1298 3832.5954) (1603.0534 3816.7939) (1605.1298 3800.9924) (1611.2366 3786.2595)
      (1620.9466 3773.6183) (1633.5878 3763.9084) (1648.3206 3757.8015) (1664.1221 3755.7252) (1679.9237 3757.8015)
      (1694.6565 3763.9084) (1707.2977 3773.6183) (1717.0076 3786.2595) (1723.1145 3800.9924) (1725.1908 3816.7939)
      (1723.1145 3832.5954) (1720.1374 3839.7557) (1725.6794 3841.1145) (1749.6641 3849.0687) (1773.8321 3858.9618)
      (1797.9237 3870.5038) (1821.6794 3883.4351) (1844.8244 3897.5115) (1867.084 3912.4427) (1888.1985 3927.9695)
      (1907.9084 3943.8168) (1925.9237 3959.7405) (1941.9847 3975.4504) (1955.8321 3990.7023) (1967.2061 4005.2061)
      (1947.3893 4000.9618) (1926.0916 3995.0534) (1903.6489 3987.6031) (1880.4122 3978.7023) (1856.7176 3968.458)
      (1832.9008 3956.9466) (1809.3282 3944.3053) (1806.0 3942.3206) (1812.3511 3950.2748) (1828.1374 3971.9237)
      (1842.6565 3993.7557) (1855.7252 4015.4046) (1867.1908 4036.5344) (1876.9008 4056.8092) (1884.687 4075.8779)
      (1890.3817 4093.4046) (1873.2214 4082.6107) (1855.2366 4069.771) (1836.7176 4055.0687) (1817.9389 4038.7481)
      (1799.1908 4020.9924) (1780.7634 4002.0153) (1762.9618 3982.0458) (1760.5191 3979.0534) (1763.7557 3988.687)
      (1771.1603 4014.458) (1777.313 4039.9389) (1782.1679 4064.7481) (1785.6947 4088.5344) (1787.8626 4110.9008)
      (1788.626 4131.4809) (1787.9695 4149.9084) (1775.5573 4133.8931) (1763.0687 4115.6489) (1750.9771 4095.9389)
      (1752.3053 4101.2061) (1755.7252 4122.1374) (1735.9847 4109.9847) (1715.6489 4095.3893) (1697.0382 4080.229)
      (1696.1527 4085.8931) (1693.4046 4099.2672) (1694.6565 4099.7863) (1707.2977 4109.4962) (1717.0076 4122.1374)
      (1723.1145 4136.8702) (1725.1908 4152.6718) (1723.1145 4168.4733) (1717.0076 4183.2061) (1707.2977 4195.8473)
      (1694.6565 4205.5573) (1679.9237 4211.6641) (1664.1221 4213.7405) (1648.3206 4211.6641) (1633.5878 4205.5573)
      (1620.9466 4195.8473) (1611.2366 4183.2061) (1605.1298 4168.4733) (1603.0534 4152.6718) (1605.1298 4136.8702)
      (1611.2366 4122.1374) (1620.9466 4109.4962) (1633.5878 4099.7863) (1648.3206 4093.6794) (1654.3206 4092.9008)
      (1652.2137 4079.3893) (1649.313 4053.7405) (1647.771 4032.0305) (1636.9313 4019.8168) (1632.0763 4030.687)
      (1620.3664 4054.1374) (1608.0916 4076.2443) (1595.4656 4096.7176) (1582.7176 4115.2214) (1570.0458 4131.4504)
      (1557.6794 4145.1145) (1558.5038 4124.8702) (1560.687 4102.8702) (1564.229 4079.4962) (1569.0382 4055.084)
      (1575.1145 4029.9847) (1582.4122 4004.5649) (1590.8702 3979.1756) (1596.1832 3965.2977) (1583.4504 3944.8092)
      (1577.084 3932.8092) (1574.0458 3940.3359) (1566.4275 3955.1298) (1557.5267 3969.313) (1547.5878 3982.7786)
      (1536.7786 3995.4046) (1525.3282 4007.0229) (1513.4504 4017.542) (1501.3282 4026.7939) (1489.1908 4034.687)
      (1477.2214 4041.0687)
    ))
    ; P2248 -- see feature_dimensions_mm.csv
    ("06_ORNAMENT" 1 (
      (1603.0534 5496.1832) (1605.1298 5480.3817) (1611.2366 5465.6489) (1620.9466 5453.0076) (1633.5878 5443.2977)
      (1648.3206 5437.1908) (1664.1221 5435.1145) (1679.9237 5437.1908) (1694.6565 5443.2977) (1707.2977 5453.0076)
      (1717.0076 5465.6489) (1723.1145 5480.3817) (1725.1908 5496.1832) (1723.1145 5511.9847) (1717.0076 5526.7176)
      (1707.2977 5539.3588) (1694.6565 5549.0687) (1679.9237 5555.1756) (1664.1221 5557.2519) (1648.3206 5555.1756)
      (1633.5878 5549.0687) (1620.9466 5539.3588) (1611.2366 5526.7176) (1605.1298 5511.9847)
    ))
    ; P2249 -- see feature_dimensions_mm.csv
    ("06_ORNAMENT" 1 (
      (1603.0534 4488.5496) (1605.1298 4472.7481) (1611.2366 4458.0153) (1620.9466 4445.374) (1633.5878 4435.6641)
      (1648.3206 4429.5573) (1664.1221 4427.4809) (1679.9237 4429.5573) (1694.6565 4435.6641) (1707.2977 4445.374)
      (1717.0076 4458.0153) (1723.1145 4472.7481) (1725.1908 4488.5496) (1723.1145 4504.3511) (1717.0076 4519.084)
      (1707.2977 4531.7252) (1694.6565 4541.4351) (1679.9237 4547.542) (1664.1221 4549.6183) (1648.3206 4547.542)
      (1633.5878 4541.4351) (1620.9466 4531.7252) (1611.2366 4519.084) (1605.1298 4504.3511)
    ))
    ; P2250 -- see feature_dimensions_mm.csv
    ("06_ORNAMENT" 1 (
      (1679.3893 6122.1374) (1755.7252 6045.8015) (1832.0611 6122.1374) (1755.7252 6198.4733)
    ))
    ; P2251 -- see feature_dimensions_mm.csv
    ("06_ORNAMENT" 1 (
      (1725.1908 7374.0458) (1786.2595 7343.5115) (1847.3282 7374.0458) (1786.2595 7404.5802)
    ))
    ; P2252 -- see feature_dimensions_mm.csv
    ("06_ORNAMENT" 1 (
      (1725.1908 7282.4427) (1786.2595 7251.9084) (1847.3282 7282.4427) (1786.2595 7312.9771)
    ))
    ; P2253 -- see feature_dimensions_mm.csv
    ("06_ORNAMENT" 1 (
      (1725.1908 7190.8397) (1786.2595 7160.3053) (1847.3282 7190.8397) (1786.2595 7221.374)
    ))
    ; P2254 -- see feature_dimensions_mm.csv
    ("06_ORNAMENT" 1 (
      (1766.1221 5302.6718) (1766.916 5280.3053) (1769.4046 5258.0916) (1773.6947 5236.3511) (1779.8626 5215.374)
      (1788.0153 5195.4656) (1798.2595 5176.916) (1810.6565 5160.0305) (1825.3282 5145.1298) (1847.145 5146.0153)
      (1868.687 5149.8168) (1889.7557 5156.2748) (1910.229 5165.0687) (1929.9237 5175.9389) (1948.687 5188.5496)
      (1966.3511 5202.6565) (1982.7481 5217.9389) (1997.7405 5234.1069) (2000.0 5236.9466) (2000.0 5308.9618)
      (1988.4122 5305.4198) (1968.4733 5297.6947) (1948.6412 5288.3664) (1929.2214 5277.5267) (1910.5191 5265.2366)
      (1892.8397 5251.5725) (1876.4733 5236.626) (1861.7557 5220.458) (1848.9771 5203.145) (1848.1985 5201.7863)
      (1849.2519 5205.9847) (1852.3664 5228.0458) (1853.313 5250.5191) (1852.2748 5273.0992) (1849.3893 5295.5115)
      (1844.855 5317.4656) (1838.8092 5338.687) (1831.4351 5358.855) (1822.8855 5377.6947) (1813.3282 5394.9313)
      (1802.9313 5410.2595) (1791.8626 5423.3893) (1784.4122 5406.3817) (1778.1069 5387.7252) (1773.0229 5367.7252)
      (1769.2824 5346.687) (1766.9466 5324.9008)
    ))
    ; P2255 -- see feature_dimensions_mm.csv
    ("06_ORNAMENT" 1 (
      (1786.2595 5709.9237) (1862.5954 5633.5878) (1938.9313 5709.9237) (1862.5954 5786.2595)
    ))
    ; P2256 -- see feature_dimensions_mm.csv
    ("06_ORNAMENT" 1 (
      (1801.8015 1851.9542) (1802.4885 1851.2824) (1811.4198 1844.0611) (1821.1603 1837.3893) (1831.5878 1831.4046)
      (1842.5954 1826.1985) (1854.0153 1821.9084) (1865.7405 1818.6565) (1877.6489 1816.5496) (1889.5878 1815.6947)
      (1901.4351 1816.2443) (1913.0534 1818.2901) (1924.3206 1821.9695) (1935.1145 1827.3893) (1927.8626 1837.6336)
      (1919.3893 1846.6107) (1909.8626 1854.3206) (1899.4656 1860.8244) (1888.3664 1866.1527) (1876.7786 1870.3359)
      (1864.855 1873.4198) (1852.7939 1875.4198) (1840.7786 1876.3969) (1828.9771 1876.3511) (1817.5725 1875.3588)
      (1806.7634 1873.4198) (1802.5038 1872.2137)
    ))
    ; P2257 -- see feature_dimensions_mm.csv
    ("06_ORNAMENT" 1 (
      (1847.3282 5923.6641) (1850.4427 5913.8626) (1859.2672 5905.1298) (1872.4427 5898.2901) (1887.9237 5893.6336)
      (1903.4046 5890.8702) (1916.7328 5889.1756) (1926.2901 5887.313) (1931.2519 5883.9695) (1931.6641 5878.0153)
      (1928.5038 5868.8092) (1923.313 5856.4122) (1917.9542 5841.6183) (1914.2443 5825.8779) (1913.5878 5811.0534)
      (1916.7328 5799.0382) (1923.6641 5791.4504) (1933.7099 5789.2366) (1945.6794 5792.5344) (1958.1985 5800.5191)
      (1969.9695 5811.5878) (1980.0916 5823.6183) (1988.2443 5834.3206) (1994.626 5841.6641) (2000.0 5844.2748)
      (2005.374 5841.6641) (2011.7557 5834.3206) (2019.9084 5823.6183) (2030.0305 5811.5878) (2041.8015 5800.5191)
      (2054.3206 5792.5344) (2066.2901 5789.2366) (2076.3359 5791.4504) (2083.2672 5799.0382) (2086.4122 5811.0534)
      (2085.7557 5825.8779) (2082.0458 5841.6183) (2076.687 5856.4122) (2071.4962 5868.8092) (2068.3359 5878.0153)
      (2068.7481 5883.9695) (2073.7099 5887.313) (2083.2672 5889.1756) (2096.5954 5890.8702) (2112.0763 5893.6336)
      (2127.5573 5898.2901) (2140.7328 5905.1298) (2149.5573 5913.8626) (2152.6718 5923.6641) (2149.5573 5933.4656)
      (2140.7328 5942.1985) (2127.5573 5949.0382) (2112.0763 5953.6947) (2096.5954 5956.458) (2083.2672 5958.1527)
      (2073.7099 5960.0153) (2068.7481 5963.3588) (2068.3359 5969.313) (2071.4962 5978.5191) (2076.687 5990.916)
      (2082.0458 6005.7099) (2085.7557 6021.4351) (2086.4122 6036.2748) (2083.2672 6048.2901) (2076.3359 6055.8779)
      (2066.2901 6058.0916) (2054.3206 6054.7939) (2041.8015 6046.8092) (2030.0305 6035.7405) (2019.9084 6023.7099)
      (2011.7557 6013.0076) (2005.374 6005.6641) (2000.0 6003.0534) (1994.626 6005.6641) (1988.2443 6013.0076)
      (1980.0916 6023.7099) (1969.9695 6035.7405) (1958.1985 6046.8092) (1945.6794 6054.7939) (1933.7099 6058.0916)
      (1923.6641 6055.8779) (1916.7328 6048.2901) (1913.5878 6036.2748) (1914.2443 6021.4351) (1917.9542 6005.7099)
      (1923.313 5990.916) (1928.5038 5978.5191) (1931.6641 5969.313) (1931.2519 5963.3588) (1926.2901 5960.0153)
      (1916.7328 5958.1527) (1903.4046 5956.458) (1887.9237 5953.6947) (1872.4427 5949.0382) (1859.2672 5942.1985)
      (1850.4427 5933.4656)
    ))
    ; P2258 -- see feature_dimensions_mm.csv
    ("06_ORNAMENT" 1 (
      (1877.8626 1740.458) (1892.6718 1731.4656) (1909.1298 1723.374) (1926.9618 1716.2901) (1945.8931 1710.3511)
      (1965.6641 1705.6641) (1986.0153 1702.3511) (2006.6565 1700.5496) (2027.3588 1700.3817) (2047.8168 1701.9695)
      (2067.7863 1705.4198) (2087.0076 1710.8702) (2105.1908 1718.4427) (2122.0763 1728.2748) (2137.4046 1740.458)
      (2121.0076 1752.6412) (2103.145 1762.4733) (2084.0916 1770.0458) (2064.1527 1775.4962) (2043.6031 1778.9466)
      (2022.7176 1780.5344) (2001.8015 1780.3664) (1981.0992 1778.5649) (1960.9313 1775.2519) (1941.5725 1770.5649)
      (1923.2977 1764.626) (1906.4122 1757.542) (1891.1603 1749.4504)
    ))
    ; P2259 -- see feature_dimensions_mm.csv
    ("06_ORNAMENT" 1 (
      (1894.7939 5448.2748) (1896.7481 5426.5038) (1900.8702 5405.374) (1907.2824 5385.1908) (1916.1527 5366.2137)
      (1927.6336 5348.7328) (1949.2061 5345.3435) (1971.0687 5344.8855) (1993.0076 5347.0992) (2000.0 5348.5802)
      (2000.0 5374.0458) (2000.2748 5378.9924) (2003.6794 5410.4275) (2004.4427 5415.1603) (2005.7099 5419.7863)
      (2011.771 5438.2595) (1995.6489 5428.4885) (1978.0611 5415.5115) (1962.1374 5401.0229) (1961.1145 5399.8473)
      (1962.9771 5403.7557) (1970.3359 5424.7786) (1975.6489 5446.626) (1979.0229 5468.9924) (1980.5802 5491.542)
      (1980.4122 5513.9542) (1978.626 5535.9389) (1975.313 5557.1603) (1970.6107 5577.313) (1964.5954 5596.0763)
      (1957.3893 5613.1298) (1949.0992 5628.1832) (1938.4733 5612.9466) (1928.6565 5595.8779) (1919.771 5577.2672)
      (1911.9847 5557.3588) (1905.4504 5536.4427) (1900.3053 5514.7939) (1896.7176 5492.7023) (1894.8244 5470.4427)
    ))
    ; P2260 -- see feature_dimensions_mm.csv
    ("06_ORNAMENT" 1 (
      (1914.0916 2085.9084) (1916.0611 2075.5725) (1919.1298 2064.9618) (1923.2519 2054.2443) (1928.3511 2043.6031)
      (1934.3969 2033.1908) (1941.3282 2023.1908) (1949.0687 2013.7557) (1957.6031 2005.0687) (1966.855 1997.2977)
      (1976.7634 1990.5954) (1987.2977 1985.145) (1998.3969 1981.1145) (2009.9847 1978.6565) (2022.0458 1977.9542)
      (2020.9008 1990.458) (2018.0305 2002.458) (2013.6489 2013.9084) (2007.8931 2024.7481) (2000.9466 2034.9008)
      (1993.0076 2044.3206) (1984.2137 2052.9466) (1974.7786 2060.7176) (1964.8397 2067.5573) (1954.6107 2073.4351)
      (1944.2443 2078.2595) (1933.9084 2082.0) (1923.8015 2084.5649)
    ))
    ; P2261 -- see feature_dimensions_mm.csv
    ("06_ORNAMENT" 1 (
      (1914.0916 1395.0076) (1924.4275 1396.9771) (1935.0382 1400.0458) (1945.7557 1404.1679) (1956.3969 1409.2672)
      (1965.6336 1414.6412) (1965.6947 1413.1603) (1967.1756 1406.8702) (1969.3282 1400.9466) (1971.4046 1395.9847)
      (1972.6718 1392.3053) (1972.5038 1389.9237) (1970.5191 1388.5802) (1966.7023 1387.8473) (1961.3588 1387.1603)
      (1955.1756 1386.0611) (1948.9771 1384.1985) (1943.7099 1381.4504) (1940.1679 1377.9695) (1938.9313 1374.0458)
      (1940.1679 1370.1221) (1943.7099 1366.6412) (1948.9771 1363.8931) (1955.1756 1362.0305) (1961.3588 1360.9313)
      (1966.7023 1360.2443) (1970.5191 1359.5115) (1972.5038 1358.1679) (1972.6718 1355.7863) (1971.4046 1352.1069)
      (1969.3282 1347.145) (1967.1756 1341.2214) (1965.6947 1334.9313) (1965.4351 1329.0076) (1966.687 1324.1985)
      (1969.4656 1321.1603) (1973.4809 1320.2748) (1978.2748 1321.5878) (1983.2824 1324.7786) (1987.9847 1329.2214)
      (1992.0458 1334.0305) (1995.2977 1338.3053) (1997.8473 1341.2519) (2000.0 1342.2901) (2002.1527 1341.2519)
      (2004.7023 1338.3053) (2007.9542 1334.0305) (2012.0153 1329.2214) (2016.7176 1324.7786) (2021.7252 1321.5878)
      (2026.5191 1320.2748) (2030.5344 1321.1603) (2033.313 1324.1985) (2034.5649 1329.0076) (2034.3053 1334.9313)
      (2032.8244 1341.2214) (2030.6718 1347.145) (2028.5954 1352.1069) (2027.3282 1355.7863) (2027.4962 1358.1679)
      (2029.4809 1359.5115) (2033.2977 1360.2443) (2038.6412 1360.9313) (2044.8244 1362.0305) (2051.0229 1363.8931)
      (2056.2901 1366.6412) (2059.8321 1370.1221) (2061.0687 1374.0458) (2059.8321 1377.9695) (2056.2901 1381.4504)
      (2051.0229 1384.1985) (2044.8244 1386.0611) (2038.6412 1387.1603) (2033.2977 1387.8473) (2029.4809 1388.5802)
      (2027.4962 1389.9237) (2027.3282 1392.3053) (2028.5954 1395.9847) (2030.6718 1400.9466) (2032.8244 1406.8702)
      (2034.3053 1413.1603) (2034.5649 1419.084) (2033.313 1423.8931) (2030.5344 1426.9313) (2026.5191 1427.8168)
      (2021.7252 1426.5038) (2016.7176 1423.313) (2012.0153 1418.8702) (2007.9542 1414.0611) (2004.7023 1409.7863)
      (2002.1527 1406.8397) (2000.0 1405.8015) (1997.8473 1406.8397) (1995.2977 1409.7863) (1992.0458 1414.0611)
      (1987.9847 1418.8702) (1983.2824 1423.313) (1980.3664 1425.1603) (1986.2443 1429.9847) (1994.9313 1438.5191)
      (2002.7023 1447.771) (2009.4046 1457.6794) (2014.855 1468.2137) (2018.8855 1479.313) (2021.3435 1490.9008)
      (2022.0458 1502.9618) (2009.542 1501.8168) (1997.542 1498.9466) (1986.0916 1494.5649) (1975.2519 1488.8092)
      (1965.0992 1481.8626) (1955.6794 1473.9237) (1947.0534 1465.1298) (1939.2824 1455.6947) (1932.4427 1445.7557)
      (1926.5649 1435.5267) (1921.7405 1425.1603) (1918.0 1414.8244) (1915.4351 1404.7176)
    ))
    ; P2262 -- see feature_dimensions_mm.csv
    ("06_ORNAMENT" 1 (
      (1928.9924 1931.2977) (1937.3282 1916.1069) (1947.542 1900.8702) (1959.4351 1885.8168) (1972.855 1871.2061)
      (1987.6336 1857.2672) (2003.6031 1844.229) (2020.5954 1832.3359) (2038.4275 1821.8473) (2056.9313 1812.9771)
      (2075.9542 1805.9847) (2095.3282 1801.1145) (2114.855 1798.5802) (2134.3969 1798.6412) (2153.771 1801.5267)
      (2145.6641 1820.2748) (2135.0992 1837.7252) (2122.3969 1853.8015) (2107.8473 1868.4885) (2091.7863 1881.771)
      (2074.4885 1893.5725) (2056.2748 1903.8931) (2037.4656 1912.6718) (2018.3359 1919.8931) (1999.2366 1925.5115)
      (1980.4275 1929.5115) (1962.2595 1931.8168) (1945.0076 1932.4275)
    ))
    ; P2263 -- see feature_dimensions_mm.csv
    ("06_ORNAMENT" 1 (
      (1928.9924 1549.6183) (1946.3206 1549.2366) (1964.6107 1550.458) (1983.6031 1553.2366) (2002.9618 1557.5573)
      (2022.4275 1563.374) (2041.7099 1570.687) (2060.4885 1579.4656) (2078.5038 1589.6641) (2095.4351 1601.2519)
      (2110.9924 1614.2443) (2124.916 1628.5649) (2136.8702 1644.2137) (2146.5802 1661.1756) (2153.771 1679.3893)
      (2133.4656 1681.7405) (2113.084 1681.313) (2092.8092 1678.3511) (2072.8092 1673.1145) (2053.2824 1665.8321)
      (2034.4122 1656.7481) (2016.3664 1646.1374) (1999.3588 1634.2443) (1983.542 1621.2977) (1969.1145 1607.5573)
      (1956.2748 1593.2672) (1945.1756 1578.687) (1936.0305 1564.0458)
    ))
    ; P2264 -- see feature_dimensions_mm.csv
    ("06_ORNAMENT" 1 (
      (1938.9313 2137.4046) (1940.1679 2133.4809) (1943.7099 2130.0) (1948.9771 2127.2519) (1955.1756 2125.3893)
      (1961.3588 2124.2901) (1966.7023 2123.6031) (1970.5191 2122.8702) (1972.5038 2121.5267) (1972.6718 2119.145)
      (1971.4046 2115.4656) (1969.3282 2110.5038) (1967.1756 2104.5802) (1965.6947 2098.2901) (1965.4351 2092.3664)
      (1966.687 2087.5573) (1969.4656 2084.5191) (1973.4809 2083.6336) (1978.2748 2084.9466) (1983.2824 2088.1374)
      (1987.9847 2092.5802) (1992.0458 2097.3893) (1995.2977 2101.6641) (1997.8473 2104.6107) (2000.0 2105.6489)
      (2002.1527 2104.6107) (2004.7023 2101.6641) (2007.9542 2097.3893) (2012.0153 2092.5802) (2016.7176 2088.1374)
      (2021.7252 2084.9466) (2026.5191 2083.6336) (2030.5344 2084.5191) (2033.313 2087.5573) (2034.5649 2092.3664)
      (2034.3053 2098.2901) (2032.8244 2104.5802) (2030.6718 2110.5038) (2028.5954 2115.4656) (2027.3282 2119.145)
      (2027.4962 2121.5267) (2029.4809 2122.8702) (2033.2977 2123.6031) (2038.6412 2124.2901) (2044.8244 2125.3893)
      (2051.0229 2127.2519) (2056.2901 2130.0) (2059.8321 2133.4809) (2061.0687 2137.4046) (2059.8321 2141.3282)
      (2056.2901 2144.8092) (2051.0229 2147.5573) (2044.8244 2149.4198) (2038.6412 2150.5191) (2033.2977 2151.2061)
      (2029.4809 2151.9389) (2027.4962 2153.2824) (2027.3282 2155.6641) (2028.5954 2159.3435) (2030.6718 2164.3053)
      (2032.8244 2170.229) (2034.3053 2176.5191) (2034.5649 2182.4427) (2033.313 2187.2519) (2030.5344 2190.2901)
      (2026.5191 2191.1756) (2021.7252 2189.8626) (2016.7176 2186.6718) (2012.0153 2182.229) (2007.9542 2177.4198)
      (2004.7023 2173.145) (2002.1527 2170.1985) (2000.0 2169.1603) (1997.8473 2170.1985) (1995.2977 2173.145)
      (1992.0458 2177.4198) (1987.9847 2182.229) (1983.2824 2186.6718) (1982.5954 2187.0992) (1980.7176 2185.8473)
      (1966.1527 2174.5954) (1967.1756 2170.229) (1969.3282 2164.3053) (1971.4046 2159.3435) (1972.6718 2155.6641)
      (1972.5038 2153.2824) (1970.5191 2151.9389) (1966.7023 2151.2061) (1961.3588 2150.5191) (1955.1756 2149.4198)
      (1948.9771 2147.5573) (1943.7099 2144.8092) (1940.1679 2141.3282)
    ))
    ; P2265 -- see feature_dimensions_mm.csv
    ("06_ORNAMENT" 1 (
      (1954.1985 5923.6641) (1956.4427 5909.5115) (1962.9466 5896.7481) (1973.084 5886.6107) (1985.8473 5880.1069)
      (2000.0 5877.8626) (2014.1527 5880.1069) (2026.916 5886.6107) (2037.0534 5896.7481) (2043.5573 5909.5115)
      (2045.8015 5923.6641) (2043.5573 5937.8168) (2037.0534 5950.5802) (2026.916 5960.7176) (2014.1527 5967.2214)
      (2000.0 5969.4656) (1985.8473 5967.2214) (1973.084 5960.7176) (1962.9466 5950.5802) (1956.4427 5937.8168)
    ))
    ; P2266 -- see feature_dimensions_mm.csv
    ("06_ORNAMENT" 1 (
      (1969.4656 3007.6336) (2000.0 2977.0992) (2030.5344 3007.6336) (2000.0 3038.1679)
    ))
    ; P2267 -- see feature_dimensions_mm.csv
    ("06_ORNAMENT" 1 (
      (1969.4656 2916.0305) (2000.0 2885.4962) (2030.5344 2916.0305) (2000.0 2946.5649)
    ))
    ; P2268 -- see feature_dimensions_mm.csv
    ("06_ORNAMENT" 1 (
      (2055.0687 5590.626) (2057.4351 5569.5725) (2062.4275 5549.2214) (2070.0153 5530.4733) (2072.8397 5533.2977)
      (2091.0382 5551.3893) (2094.5344 5554.5344) (2125.8473 5579.8473) (2128.9008 5582.1221) (2136.3817 5587.2061)
      (2132.7634 5585.4962) (2114.3206 5574.3969) (2113.084 5573.4351) (2115.6794 5576.9008) (2126.9924 5596.0916)
      (2136.458 5616.4885) (2144.1374 5637.7557) (2150.0611 5659.5725) (2154.2748 5681.6031) (2156.7939 5703.4962)
      (2157.7099 5724.9618) (2157.0229 5745.6489) (2154.7786 5765.2214) (2151.0534 5783.3588) (2145.8473 5799.7252)
      (2132.458 5786.8702) (2119.4962 5772.0458) (2107.145 5755.5115) (2095.6336 5737.5115) (2085.1298 5718.2748)
      (2075.8779 5698.0458) (2068.0458 5677.084) (2061.8473 5655.6183) (2057.4809 5633.8779) (2055.1603 5612.1374)
    ))
    ; P2269 -- see feature_dimensions_mm.csv
    ("06_ORNAMENT" 1 (
      (2067.5725 1425.9237) (2068.7023 1409.9084) (2083.8931 1418.2443) (2099.1298 1428.458) (2114.1832 1440.3511)
      (2128.7939 1453.771) (2142.7328 1468.5496) (2155.771 1484.5191) (2167.6641 1501.4962) (2178.1527 1519.3435)
      (2187.0229 1537.8473) (2194.0153 1556.8702) (2198.8855 1576.2443) (2201.4198 1595.771) (2201.3588 1615.313)
      (2198.4733 1634.687) (2179.7252 1626.5802) (2162.2748 1616.0153) (2146.1985 1603.313) (2131.5115 1588.7634)
      (2118.229 1572.7023) (2106.4275 1555.4046) (2096.1069 1537.1908) (2087.3282 1518.3817) (2080.1069 1499.2519)
      (2074.4885 1480.1527) (2070.4885 1461.3435) (2068.1832 1443.1756)
    ))
    ; P2270 -- see feature_dimensions_mm.csv
    ("06_ORNAMENT" 1 (
      (2068.3206 2053.6794) (2069.542 2035.3893) (2072.3206 2016.3969) (2076.6412 1997.0382) (2082.458 1977.5725)
      (2089.771 1958.2901) (2098.5496 1939.5115) (2108.7481 1921.4962) (2120.3359 1904.5649) (2133.3282 1889.0076)
      (2147.6489 1875.084) (2163.2977 1863.1298) (2180.2595 1853.4198) (2198.4733 1846.229) (2200.8244 1866.5344)
      (2200.3969 1886.916) (2197.4351 1907.1908) (2192.1985 1927.1908) (2184.916 1946.7176) (2175.8321 1965.5878)
      (2165.2214 1983.6336) (2153.3282 2000.6412) (2140.3817 2016.458) (2126.6412 2030.8855) (2112.3511 2043.7252)
      (2097.771 2054.8244) (2083.1298 2063.9695) (2068.7023 2071.0076)
    ))
    ; P2271 -- see feature_dimensions_mm.csv
    ("06_ORNAMENT" 1 (
      (2123.6031 1321.6947) (2123.6489 1309.8931) (2124.6412 1298.4885) (2126.5802 1287.6794) (2129.4046 1277.6489)
      (2133.0992 1268.5496) (2141.0687 1275.4351) (2148.7176 1283.4046) (2155.9389 1292.3359) (2162.6107 1302.0763)
      (2168.5954 1312.5038) (2173.8015 1323.5115) (2178.0916 1334.9313) (2181.3435 1346.6565) (2183.4504 1358.5649)
      (2184.3053 1370.5038) (2183.7557 1382.3511) (2181.7099 1393.9695) (2178.0305 1405.2366) (2172.6107 1416.0305)
      (2162.3664 1408.7786) (2153.3893 1400.3053) (2145.6794 1390.7786) (2139.1756 1380.3817) (2133.8473 1369.2824)
      (2129.6641 1357.6947) (2126.5802 1345.771) (2124.5802 1333.7099)
    ))
    ; P2272 -- see feature_dimensions_mm.csv
    ("06_ORNAMENT" 1 (
      (2124.3053 2168.5802) (2124.3206 2156.5496) (2125.3282 2144.4122) (2127.3282 2132.3817) (2130.3664 2120.5954)
      (2134.4885 2109.2366) (2139.7252 2098.4733) (2146.1221 2088.4885) (2153.7099 2079.4504) (2162.5191 2071.5267)
      (2172.6107 2064.8855) (2177.8626 2076.2901) (2181.3893 2088.1069) (2183.313 2100.229) (2183.7405 2112.4885)
      (2182.8092 2124.7481) (2180.6412 2136.8855) (2177.3435 2148.7481) (2173.0534 2160.1985) (2167.8779 2171.084)
      (2161.9542 2181.2977) (2155.3893 2190.6565) (2148.3053 2199.0534) (2140.8397 2206.3359) (2133.0992 2212.3664)
      (2129.6336 2202.4122) (2126.9924 2191.6794) (2125.2061 2180.3511)
    ))
    ; P2273 -- see feature_dimensions_mm.csv
    ("06_ORNAMENT" 1 (
      (2152.6718 1740.458) (2154.7328 1719.6031) (2160.8092 1699.5573) (2170.687 1681.084) (2183.9695 1664.8855)
      (2200.1679 1651.6031) (2218.6412 1641.7252) (2238.687 1635.6336) (2259.542 1633.5878) (2280.3969 1635.6336)
      (2300.4427 1641.7252) (2318.916 1651.6031) (2335.1145 1664.8855) (2348.3969 1681.084) (2358.2748 1699.5573)
      (2364.3664 1719.6031) (2366.4122 1740.458) (2364.3664 1761.313) (2358.2748 1781.3588) (2348.3969 1799.8321)
      (2335.1145 1816.0305) (2318.916 1829.313) (2300.4427 1839.1908) (2280.3969 1845.2672) (2259.542 1847.3282)
      (2238.687 1845.2672) (2218.6412 1839.1908) (2200.1679 1829.313) (2183.9695 1816.0305) (2170.687 1799.8321)
      (2160.8092 1781.3588) (2154.7328 1761.313)
    ))
    ; P2274 -- see feature_dimensions_mm.csv
    ("06_ORNAMENT" 1 (
      (2183.2061 1740.458) (2184.6718 1725.5725) (2189.0229 1711.2519) (2196.0763 1698.0458) (2205.5573 1686.4733)
      (2217.1298 1676.9924) (2230.3359 1669.9389) (2244.6565 1665.5878) (2259.542 1664.1221) (2274.4275 1665.5878)
      (2288.7481 1669.9389) (2301.9542 1676.9924) (2313.5267 1686.4733) (2323.0076 1698.0458) (2330.0611 1711.2519)
      (2334.4122 1725.5725) (2335.8779 1740.458) (2334.4122 1755.3435) (2330.0611 1769.6641) (2323.0076 1782.8702)
      (2313.5267 1794.4427) (2301.9542 1803.9237) (2288.7481 1810.9771) (2274.4275 1815.3282) (2259.542 1816.7939)
      (2244.6565 1815.3282) (2230.3359 1810.9771) (2217.1298 1803.9237) (2205.5573 1794.4427) (2196.0763 1782.8702)
      (2189.0229 1769.6641) (2184.6718 1755.3435)
    ))
    ; P2275 -- see feature_dimensions_mm.csv
    ("06_ORNAMENT" 1 (
      (2198.4733 7374.0458) (2259.542 7343.5115) (2320.6107 7374.0458) (2259.542 7404.5802)
    ))
    ; P2276 -- see feature_dimensions_mm.csv
    ("06_ORNAMENT" 1 (
      (2198.4733 7282.4427) (2259.542 7251.9084) (2320.6107 7282.4427) (2259.542 7312.9771)
    ))
    ; P2277 -- see feature_dimensions_mm.csv
    ("06_ORNAMENT" 1 (
      (2198.4733 7190.8397) (2259.542 7160.3053) (2320.6107 7190.8397) (2259.542 7221.374)
    ))
    ; P2278 -- see feature_dimensions_mm.csv
    ("06_ORNAMENT" 1 (
      (2219.4656 1972.6412) (2221.0534 1952.1832) (2224.5038 1932.2137) (2229.9542 1912.9924) (2237.5267 1894.8092)
      (2247.3588 1877.9237) (2259.542 1862.5954) (2271.7252 1878.9924) (2281.5573 1896.855) (2289.1298 1915.9084)
      (2294.5802 1935.8473) (2298.0305 1956.3969) (2299.6183 1977.2824) (2299.4504 1998.1985) (2297.6489 2018.9008)
      (2294.3359 2039.0687) (2289.6489 2058.4275) (2283.7099 2076.7023) (2276.626 2093.5878) (2268.5344 2108.8397)
      (2259.542 2122.1374) (2250.5496 2107.3282) (2242.458 2090.8702) (2235.374 2073.0382) (2229.4351 2054.1069)
      (2224.7481 2034.3359) (2221.4351 2013.9847) (2219.6336 1993.3435)
    ))
    ; P2279 -- see feature_dimensions_mm.csv
    ("06_ORNAMENT" 1 (
      (2219.4656 1503.6336) (2219.6336 1482.7023) (2221.4351 1462.0153) (2224.7481 1441.8473) (2229.4351 1422.4885)
      (2235.374 1404.2137) (2242.458 1387.313) (2250.5496 1372.0763) (2259.542 1358.7786) (2268.5344 1373.5878)
      (2276.626 1390.0458) (2283.7099 1407.8779) (2289.6489 1426.8092) (2294.3359 1446.5802) (2297.6489 1466.916)
      (2299.4504 1487.5725) (2299.6183 1508.2748) (2298.0305 1528.7328) (2294.5802 1548.7023) (2289.1298 1567.9237)
      (2281.5573 1586.1069) (2271.7252 1602.9924) (2259.542 1618.3206) (2247.3588 1601.9237) (2237.5267 1584.0611)
      (2229.9542 1565.0076) (2224.5038 1545.0687) (2221.0534 1524.5191)
    ))
    ; P2280 -- see feature_dimensions_mm.csv
    ("06_ORNAMENT" 1 (
      (2242.916 5722.9618) (2243.8473 5702.0458) (2247.771 5681.4962) (2266.3969 5670.1069) (2276.7023 5665.5878)
      (2297.9237 5675.2366) (2299.5878 5675.9542) (2347.0534 5695.3282) (2348.4885 5695.8931) (2397.7863 5714.1069)
      (2399.0534 5714.5496) (2444.5649 5729.8779) (2429.8779 5732.0916) (2407.7099 5733.8626) (2385.3282 5734.0305)
      (2363.0382 5732.5038) (2341.1298 5729.1603) (2319.9084 5723.8931) (2299.6489 5716.5954) (2298.2595 5715.9084)
      (2301.4656 5718.7939) (2316.3206 5735.4198) (2329.5878 5753.5725) (2341.2672 5772.9313) (2351.3282 5793.1756)
      (2359.7405 5813.9542) (2366.5038 5834.9466) (2371.5725 5855.8168) (2374.9466 5876.229) (2375.3435 5881.084)
      (2378.5954 5881.9847) (2389.8626 5889.1603) (2400.458 5899.1298) (2409.5725 5909.9542) (2416.9008 5919.5878)
      (2422.6412 5926.1985) (2427.4809 5928.5496) (2432.3206 5926.1985) (2438.0611 5919.5878) (2445.3893 5909.9542)
      (2454.5038 5899.1298) (2465.0992 5889.1603) (2473.1756 5884.0153) (2470.8092 5879.6794) (2462.4885 5859.8321)
      (2456.6107 5839.4809) (2453.4504 5818.7786) (2453.2824 5797.8626) (2469.3282 5783.0534) (2487.2519 5770.5344)
      (2506.7328 5760.1832) (2522.9313 5753.7252) (2555.3282 5762.9313) (2556.2137 5763.1756) (2608.1221 5776.7939)
      (2608.9313 5777.0076) (2660.3359 5789.4962) (2661.0687 5789.6794) (2683.9389 5794.8397) (2681.9389 5795.8931)
      (2662.3817 5804.5191) (2641.771 5811.9542) (2620.3664 5818.0153) (2598.458 5822.5649) (2576.2901 5825.4046)
      (2554.1527 5826.3969) (2532.3053 5825.374) (2511.0229 5822.1679) (2509.5115 5821.771) (2513.2366 5823.9695)
      (2531.0382 5837.374) (2547.5878 5852.5954) (2562.8244 5869.313) (2576.6412 5887.1908) (2588.9466 5905.9237)
      (2599.6794 5925.1908) (2608.7176 5944.6718) (2616.0 5964.0458) (2621.4351 5982.9924) (2624.916 6001.1756)
      (2626.3817 6018.2901) (2609.084 6011.5267) (2591.4351 6002.8092) (2573.7099 5992.2443) (2556.1679 5980.0153)
      (2539.1145 5966.2595) (2522.8244 5951.1298) (2507.5573 5934.7481) (2501.1298 5926.687) (2496.5038 5939.4656)
      (2491.8321 5950.626) (2488.9771 5958.916) (2489.3588 5964.2748) (2493.8168 5967.2824) (2502.4122 5968.9618)
      (2514.4122 5970.4885) (2528.3511 5972.9771) (2542.2748 5977.1603) (2554.1374 5983.3282) (2562.0916 5991.1756)
      (2564.8855 6000.0) (2562.0916 6008.8244) (2554.1374 6016.6718) (2542.2748 6022.8397) (2528.3511 6027.0229)
      (2514.4122 6029.5115) (2502.4122 6031.0382) (2493.8168 6032.7176) (2489.3588 6035.7252) (2488.9771 6041.084)
      (2491.8321 6049.374) (2496.5038 6060.5344) (2501.3282 6073.8473) (2504.6565 6088.0) (2505.2519 6101.3435)
      (2502.4275 6112.1679) (2496.1832 6118.9924) (2487.145 6120.9771) (2476.3664 6118.0153) (2465.0992 6110.8397)
      (2454.5038 6100.8702) (2445.3893 6090.0458) (2438.0611 6080.4122) (2432.3206 6073.8015) (2427.4809 6071.4504)
      (2422.6412 6073.8015) (2416.9008 6080.4122) (2409.5725 6090.0458) (2400.458 6100.8702) (2389.8626 6110.8397)
      (2378.5954 6118.0153) (2367.8168 6120.9771) (2358.7786 6118.9924) (2352.5344 6112.1679) (2349.7099 6101.3435)
      (2350.3053 6088.0) (2353.6336 6073.8473) (2358.458 6060.5344) (2363.1298 6049.374) (2365.9847 6041.084)
      (2365.6031 6035.7252) (2361.145 6032.7176) (2352.5496 6031.0382) (2340.5496 6029.5115) (2326.6107 6027.0229)
      (2312.687 6022.8397) (2300.8244 6016.6718) (2292.8702 6008.8244) (2290.0763 6000.0) (2292.8702 5991.1756)
      (2300.8244 5983.3282) (2312.687 5977.1603) (2326.6107 5972.9771) (2340.5496 5970.4885) (2352.5496 5968.9618)
      (2361.145 5967.2824) (2365.6031 5964.2748) (2365.9847 5958.916) (2363.1298 5950.626) (2358.458 5939.4656)
      (2353.6336 5926.1527) (2351.1298 5915.4809) (2343.2824 5909.4504) (2327.9542 5895.6336) (2313.145 5880.229)
      (2299.0992 5863.4046) (2286.0763 5845.374) (2274.3053 5826.3359) (2264.0305 5806.4885) (2255.5115 5786.0305)
      (2248.9924 5765.1603) (2244.7176 5744.0763)
    ))
    ; P2281 -- see feature_dimensions_mm.csv
    ("06_ORNAMENT" 1 (
      (2259.542 3007.6336) (2290.0763 2977.0992) (2320.6107 3007.6336) (2290.0763 3038.1679)
    ))
    ; P2282 -- see feature_dimensions_mm.csv
    ("06_ORNAMENT" 1 (
      (2259.542 2916.0305) (2290.0763 2885.4962) (2320.6107 2916.0305) (2290.0763 2946.5649)
    ))
    ; P2283 -- see feature_dimensions_mm.csv
    ("06_ORNAMENT" 1 (
      (2287.7863 5175.8321) (2289.4809 5172.687) (2294.1069 5170.1374) (2300.4122 5168.4733) (2306.7328 5167.6031)
      (2311.4656 5167.0229) (2313.5725 5165.9542) (2312.8397 5163.7099) (2309.9084 5159.9542) (2306.0458 5154.8855)
      (2302.7634 5149.2519) (2301.2977 5144.1679) (2302.3206 5140.7481) (2305.7405 5139.7252) (2310.8244 5141.1908)
      (2316.458 5144.4733) (2321.5267 5148.3206) (2325.2824 5151.2519) (2327.5267 5151.9847) (2328.5954 5149.8931)
      (2329.1908 5145.1603) (2330.0458 5138.8397) (2331.7099 5132.5344) (2334.2595 5127.9084) (2337.4046 5126.2137)
      (2340.5496 5127.9084) (2343.0992 5132.5344) (2344.7634 5138.8397) (2345.6183 5145.1603) (2346.2137 5149.8931)
      (2347.2824 5151.9847) (2349.5267 5151.2519) (2353.2824 5148.3206) (2358.3511 5144.4733) (2363.9847 5141.1908)
      (2369.0687 5139.7252) (2372.4885 5140.7481) (2373.5115 5144.1679) (2372.0458 5149.2519) (2368.7634 5154.8855)
      (2364.9008 5159.9542) (2361.9695 5163.7099) (2361.2366 5165.9542) (2363.3435 5167.0229) (2368.0763 5167.6031)
      (2374.3969 5168.4733) (2380.7023 5170.1374) (2385.3282 5172.687) (2387.0229 5175.8321) (2385.3282 5178.9771)
      (2380.7023 5181.5267) (2374.3969 5183.1908) (2368.0763 5184.0458) (2363.3435 5184.6412) (2361.2366 5185.7099)
      (2361.9695 5187.9542) (2364.9008 5191.7099) (2368.7634 5196.7786) (2372.0458 5202.4122) (2373.5115 5207.4962)
      (2372.4885 5210.916) (2369.0687 5211.9389) (2363.9847 5210.4733) (2358.3511 5207.1908) (2353.2824 5203.3282)
      (2349.5267 5200.3969) (2347.2824 5199.6641) (2346.2137 5201.771) (2345.6183 5206.5038) (2344.7634 5212.8092)
      (2343.0992 5219.1145) (2340.5496 5223.7557) (2337.4046 5225.4504) (2334.2595 5223.7557) (2331.7099 5219.1145)
      (2330.0458 5212.8092) (2329.1908 5206.5038) (2328.5954 5201.771) (2327.5267 5199.6641) (2325.2824 5200.3969)
      (2321.5267 5203.3282) (2316.458 5207.1908) (2310.8244 5210.4733) (2305.7405 5211.9389) (2302.3206 5210.916)
      (2301.2977 5207.4962) (2302.7634 5202.4122) (2306.0458 5196.7786) (2309.9084 5191.7099) (2312.8397 5187.9542)
      (2313.5725 5185.7099) (2311.4656 5184.6412) (2306.7328 5184.0458) (2300.4122 5183.1908) (2294.1069 5181.5267)
      (2289.4809 5178.9771)
    ))
    ; P2284 -- see feature_dimensions_mm.csv
    ("06_ORNAMENT" 1 (
      (2287.7863 4864.3817) (2289.4809 4861.2366) (2294.1069 4858.687) (2300.4122 4857.0229) (2306.7328 4856.1527)
      (2311.4656 4855.5725) (2313.5725 4854.5038) (2312.8397 4852.2595) (2309.9084 4848.5038) (2306.0458 4843.4351)
      (2302.7634 4837.8015) (2301.2977 4832.7176) (2302.3206 4829.2977) (2305.7405 4828.2748) (2310.8244 4829.7405)
      (2316.458 4833.0229) (2321.5267 4836.8702) (2325.2824 4839.8015) (2327.5267 4840.5344) (2328.5954 4838.4427)
      (2329.1908 4833.7099) (2330.0458 4827.3893) (2331.7099 4821.084) (2334.2595 4816.458) (2337.4046 4814.7634)
      (2340.5496 4816.458) (2343.0992 4821.084) (2344.7634 4827.3893) (2345.6183 4833.7099) (2346.2137 4838.4427)
      (2347.2824 4840.5344) (2349.5267 4839.8015) (2353.2824 4836.8702) (2358.3511 4833.0229) (2363.9847 4829.7405)
      (2369.0687 4828.2748) (2372.4885 4829.2977) (2373.5115 4832.7176) (2372.0458 4837.8015) (2368.7634 4843.4351)
      (2364.9008 4848.5038) (2361.9695 4852.2595) (2361.2366 4854.5038) (2363.3435 4855.5725) (2368.0763 4856.1527)
      (2374.3969 4857.0229) (2380.7023 4858.687) (2385.3282 4861.2366) (2387.0229 4864.3817) (2385.3282 4867.5267)
      (2380.7023 4870.0763) (2374.3969 4871.7405) (2368.0763 4872.5954) (2363.3435 4873.1908) (2361.2366 4874.2595)
      (2361.9695 4876.5038) (2364.9008 4880.2595) (2368.7634 4885.3282) (2372.0458 4890.9618) (2373.5115 4896.0458)
      (2372.4885 4899.4656) (2369.0687 4900.4885) (2363.9847 4899.0229) (2358.3511 4895.7405) (2353.2824 4891.8779)
      (2349.5267 4888.9466) (2347.2824 4888.2137) (2346.2137 4890.3206) (2345.6183 4895.0534) (2344.7634 4901.3588)
      (2343.0992 4907.6641) (2340.5496 4912.3053) (2337.4046 4914.0) (2334.2595 4912.3053) (2331.7099 4907.6641)
      (2330.0458 4901.3588) (2329.1908 4895.0534) (2328.5954 4890.3206) (2327.5267 4888.2137) (2325.2824 4888.9466)
      (2321.5267 4891.8779) (2316.458 4895.7405) (2310.8244 4899.0229) (2305.7405 4900.4885) (2302.3206 4899.4656)
      (2301.2977 4896.0458) (2302.7634 4890.9618) (2306.0458 4885.3282) (2309.9084 4880.2595) (2312.8397 4876.5038)
      (2313.5725 4874.2595) (2311.4656 4873.1908) (2306.7328 4872.5954) (2300.4122 4871.7405) (2294.1069 4870.0763)
      (2289.4809 4867.5267)
    ))
    ; P2285 -- see feature_dimensions_mm.csv
    ("06_ORNAMENT" 1 (
      (2287.7863 4552.9313) (2289.4809 4549.7863) (2294.1069 4547.2366) (2300.4122 4545.5725) (2306.7328 4544.7023)
      (2311.4656 4544.1221) (2313.5725 4543.0534) (2312.8397 4540.8092) (2309.9084 4537.0534) (2306.0458 4531.9847)
      (2302.7634 4526.3511) (2301.2977 4521.2672) (2302.3206 4517.8473) (2305.7405 4516.8244) (2310.8244 4518.2901)
      (2316.458 4521.5725) (2321.5267 4525.4198) (2325.2824 4528.3511) (2327.5267 4529.084) (2328.5954 4526.9924)
      (2329.1908 4522.2595) (2330.0458 4515.9389) (2331.7099 4509.6336) (2334.2595 4505.0076) (2337.4046 4503.313)
      (2340.5496 4505.0076) (2343.0992 4509.6336) (2344.7634 4515.9389) (2345.6183 4522.2595) (2346.2137 4526.9924)
      (2347.2824 4529.084) (2349.5267 4528.3511) (2353.2824 4525.4198) (2358.3511 4521.5725) (2363.9847 4518.2901)
      (2369.0687 4516.8244) (2372.4885 4517.8473) (2373.5115 4521.2672) (2372.0458 4526.3511) (2368.7634 4531.9847)
      (2364.9008 4537.0534) (2361.9695 4540.8092) (2361.2366 4543.0534) (2363.3435 4544.1221) (2368.0763 4544.7023)
      (2374.3969 4545.5725) (2380.7023 4547.2366) (2385.3282 4549.7863) (2387.0229 4552.9313) (2385.3282 4556.0763)
      (2380.7023 4558.626) (2374.3969 4560.2901) (2368.0763 4561.145) (2363.3435 4561.7405) (2361.2366 4562.8092)
      (2361.9695 4565.0534) (2364.9008 4568.8092) (2368.7634 4573.8779) (2372.0458 4579.5115) (2373.5115 4584.5954)
      (2372.4885 4588.0153) (2369.0687 4589.0382) (2363.9847 4587.5725) (2358.3511 4584.2901) (2353.2824 4580.4275)
      (2349.5267 4577.4962) (2347.2824 4576.7634) (2346.2137 4578.8702) (2345.6183 4583.6031) (2344.7634 4589.9084)
      (2343.0992 4596.2137) (2340.5496 4600.855) (2337.4046 4602.5496) (2334.2595 4600.855) (2331.7099 4596.2137)
      (2330.0458 4589.9084) (2329.1908 4583.6031) (2328.5954 4578.8702) (2327.5267 4576.7634) (2325.2824 4577.4962)
      (2321.5267 4580.4275) (2316.458 4584.2901) (2310.8244 4587.5725) (2305.7405 4589.0382) (2302.3206 4588.0153)
      (2301.2977 4584.5954) (2302.7634 4579.5115) (2306.0458 4573.8779) (2309.9084 4568.8092) (2312.8397 4565.0534)
      (2313.5725 4562.8092) (2311.4656 4561.7405) (2306.7328 4561.145) (2300.4122 4560.2901) (2294.1069 4558.626)
      (2289.4809 4556.0763)
    ))
    ; P2286 -- see feature_dimensions_mm.csv
    ("06_ORNAMENT" 1 (
      (2287.7863 4241.4809) (2289.4809 4238.3359) (2294.1069 4235.7863) (2300.4122 4234.1221) (2306.7328 4233.2519)
      (2311.4656 4232.6718) (2313.5725 4231.6031) (2312.8397 4229.3588) (2309.9084 4225.6031) (2306.0458 4220.5344)
      (2302.7634 4214.9008) (2301.2977 4209.8168) (2302.3206 4206.3969) (2305.7405 4205.374) (2310.8244 4206.8397)
      (2316.458 4210.1221) (2321.5267 4213.9695) (2325.2824 4216.9008) (2327.5267 4217.6336) (2328.5954 4215.542)
      (2329.1908 4210.8092) (2330.0458 4204.4885) (2331.7099 4198.1832) (2334.2595 4193.5573) (2337.4046 4191.8626)
      (2340.5496 4193.5573) (2343.0992 4198.1832) (2344.7634 4204.4885) (2345.6183 4210.8092) (2346.2137 4215.542)
      (2347.2824 4217.6336) (2349.5267 4216.9008) (2353.2824 4213.9695) (2358.3511 4210.1221) (2363.9847 4206.8397)
      (2369.0687 4205.374) (2372.4885 4206.3969) (2373.5115 4209.8168) (2372.0458 4214.9008) (2368.7634 4220.5344)
      (2364.9008 4225.6031) (2361.9695 4229.3588) (2361.2366 4231.6031) (2363.3435 4232.6718) (2368.0763 4233.2519)
      (2374.3969 4234.1221) (2380.7023 4235.7863) (2385.3282 4238.3359) (2387.0229 4241.4809) (2385.3282 4244.626)
      (2380.7023 4247.1756) (2374.3969 4248.8397) (2368.0763 4249.6947) (2363.3435 4250.2901) (2361.2366 4251.3588)
      (2361.9695 4253.6031) (2364.9008 4257.3588) (2368.7634 4262.4275) (2372.0458 4268.0611) (2373.5115 4273.145)
      (2372.4885 4276.5649) (2369.0687 4277.5878) (2363.9847 4276.1221) (2358.3511 4272.8397) (2353.2824 4268.9771)
      (2349.5267 4266.0458) (2347.2824 4265.313) (2346.2137 4267.4198) (2345.6183 4272.1527) (2344.7634 4278.458)
      (2343.0992 4284.7634) (2340.5496 4289.4046) (2337.4046 4291.0992) (2334.2595 4289.4046) (2331.7099 4284.7634)
      (2330.0458 4278.458) (2329.1908 4272.1527) (2328.5954 4267.4198) (2327.5267 4265.313) (2325.2824 4266.0458)
      (2321.5267 4268.9771) (2316.458 4272.8397) (2310.8244 4276.1221) (2305.7405 4277.5878) (2302.3206 4276.5649)
      (2301.2977 4273.145) (2302.7634 4268.0611) (2306.0458 4262.4275) (2309.9084 4257.3588) (2312.8397 4253.6031)
      (2313.5725 4251.3588) (2311.4656 4250.2901) (2306.7328 4249.6947) (2300.4122 4248.8397) (2294.1069 4247.1756)
      (2289.4809 4244.626)
    ))
    ; P2287 -- see feature_dimensions_mm.csv
    ("06_ORNAMENT" 1 (
      (2287.7863 3930.0305) (2289.4809 3926.8855) (2294.1069 3924.3359) (2300.4122 3922.6718) (2306.7328 3921.8015)
      (2311.4656 3921.2214) (2313.5725 3920.1527) (2312.8397 3917.9084) (2309.9084 3914.1527) (2306.0458 3909.084)
      (2302.7634 3903.4504) (2301.2977 3898.3664) (2302.3206 3894.9466) (2305.7405 3893.9237) (2310.8244 3895.3893)
      (2316.458 3898.6718) (2321.5267 3902.5191) (2325.2824 3905.4504) (2327.5267 3906.1832) (2328.5954 3904.0916)
      (2329.1908 3899.3588) (2330.0458 3893.0382) (2331.7099 3886.7328) (2334.2595 3882.1069) (2337.4046 3880.4122)
      (2340.5496 3882.1069) (2343.0992 3886.7328) (2344.7634 3893.0382) (2345.6183 3899.3588) (2346.2137 3904.0916)
      (2347.2824 3906.1832) (2349.5267 3905.4504) (2353.2824 3902.5191) (2358.3511 3898.6718) (2363.9847 3895.3893)
      (2369.0687 3893.9237) (2372.4885 3894.9466) (2373.5115 3898.3664) (2372.0458 3903.4504) (2368.7634 3909.084)
      (2364.9008 3914.1527) (2361.9695 3917.9084) (2361.2366 3920.1527) (2363.3435 3921.2214) (2368.0763 3921.8015)
      (2374.3969 3922.6718) (2380.7023 3924.3359) (2385.3282 3926.8855) (2387.0229 3930.0305) (2385.3282 3933.1756)
      (2380.7023 3935.7252) (2374.3969 3937.3893) (2368.0763 3938.2443) (2363.3435 3938.8397) (2361.2366 3939.9084)
      (2361.9695 3942.1527) (2364.9008 3945.9084) (2368.7634 3950.9771) (2372.0458 3956.6107) (2373.5115 3961.6947)
      (2372.4885 3965.1145) (2369.0687 3966.1374) (2363.9847 3964.6718) (2358.3511 3961.3893) (2353.2824 3957.5267)
      (2349.5267 3954.5954) (2347.2824 3953.8626) (2346.2137 3955.9695) (2345.6183 3960.7023) (2344.7634 3967.0076)
      (2343.0992 3973.313) (2340.5496 3977.9542) (2337.4046 3979.6489) (2334.2595 3977.9542) (2331.7099 3973.313)
      (2330.0458 3967.0076) (2329.1908 3960.7023) (2328.5954 3955.9695) (2327.5267 3953.8626) (2325.2824 3954.5954)
      (2321.5267 3957.5267) (2316.458 3961.3893) (2310.8244 3964.6718) (2305.7405 3966.1374) (2302.3206 3965.1145)
      (2301.2977 3961.6947) (2302.7634 3956.6107) (2306.0458 3950.9771) (2309.9084 3945.9084) (2312.8397 3942.1527)
      (2313.5725 3939.9084) (2311.4656 3938.8397) (2306.7328 3938.2443) (2300.4122 3937.3893) (2294.1069 3935.7252)
      (2289.4809 3933.1756)
    ))
    ; P2288 -- see feature_dimensions_mm.csv
    ("06_ORNAMENT" 1 (
      (2317.6641 1885.145) (2317.7252 1865.6031) (2320.6107 1846.229) (2339.3588 1854.3359) (2356.8092 1864.9008)
      (2372.8855 1877.6031) (2387.5725 1892.1527) (2400.855 1908.2137) (2412.6565 1925.5115) (2422.9771 1943.7252)
      (2431.7557 1962.5344) (2438.9771 1981.6641) (2444.5954 2000.7634) (2448.5954 2019.5725) (2450.9008 2037.7405)
      (2451.5115 2054.9924) (2450.3817 2071.0076) (2435.1908 2062.6718) (2419.9542 2052.458) (2404.916 2040.5649)
      (2390.2901 2027.145) (2376.3511 2012.3664) (2363.313 1996.3969) (2351.4198 1979.4046) (2340.9313 1961.5725)
      (2332.0611 1943.0687) (2325.0687 1924.0458) (2320.1985 1904.6718)
    ))
    ; P2289 -- see feature_dimensions_mm.csv
    ("06_ORNAMENT" 1 (
      (2318.2595 1614.3817) (2318.687 1594.0) (2321.6489 1573.7252) (2326.8855 1553.7252) (2334.1679 1534.1985)
      (2343.2519 1515.3282) (2353.8626 1497.2824) (2365.7557 1480.2748) (2378.7023 1464.458) (2392.4427 1450.0305)
      (2406.7328 1437.1908) (2421.313 1426.0916) (2435.9542 1416.9466) (2450.3817 1409.9084) (2450.7634 1427.2366)
      (2449.542 1445.5267) (2446.7634 1464.5191) (2442.4427 1483.8779) (2436.626 1503.3435) (2429.313 1522.626)
      (2420.5344 1541.4046) (2410.3359 1559.4198) (2398.7481 1576.3511) (2385.7557 1591.9084) (2371.4351 1605.8321)
      (2355.7863 1617.7863) (2338.8244 1627.4962) (2320.6107 1634.687)
    ))
    ; P2290 -- see feature_dimensions_mm.csv
    ("06_ORNAMENT" 1 (
      (2325.4962 5175.8321) (2326.3969 5171.2672) (2328.9771 5167.4046) (2332.855 5164.8244) (2337.4046 5163.9237)
      (2341.9542 5164.8244) (2345.8321 5167.4046) (2348.4122 5171.2672) (2349.313 5175.8321) (2348.4122 5180.3817)
      (2345.8321 5184.2443) (2341.9542 5186.8244) (2337.4046 5187.7405) (2332.855 5186.8244) (2328.9771 5184.2443)
      (2326.3969 5180.3817)
    ))
    ; P2291 -- see feature_dimensions_mm.csv
    ("06_ORNAMENT" 1 (
      (2325.4962 4864.3817) (2326.3969 4859.8168) (2328.9771 4855.9542) (2332.855 4853.374) (2337.4046 4852.4733)
      (2341.9542 4853.374) (2345.8321 4855.9542) (2348.4122 4859.8168) (2349.313 4864.3817) (2348.4122 4868.9313)
      (2345.8321 4872.7939) (2341.9542 4875.374) (2337.4046 4876.2901) (2332.855 4875.374) (2328.9771 4872.7939)
      (2326.3969 4868.9313)
    ))
    ; P2292 -- see feature_dimensions_mm.csv
    ("06_ORNAMENT" 1 (
      (2325.4962 4552.9313) (2326.3969 4548.3664) (2328.9771 4544.5038) (2332.855 4541.9237) (2337.4046 4541.0229)
      (2341.9542 4541.9237) (2345.8321 4544.5038) (2348.4122 4548.3664) (2349.313 4552.9313) (2348.4122 4557.4809)
      (2345.8321 4561.3435) (2341.9542 4563.9237) (2337.4046 4564.8397) (2332.855 4563.9237) (2328.9771 4561.3435)
      (2326.3969 4557.4809)
    ))
    ; P2293 -- see feature_dimensions_mm.csv
    ("06_ORNAMENT" 1 (
      (2325.4962 4241.4809) (2326.3969 4236.916) (2328.9771 4233.0534) (2332.855 4230.4733) (2337.4046 4229.5725)
      (2341.9542 4230.4733) (2345.8321 4233.0534) (2348.4122 4236.916) (2349.313 4241.4809) (2348.4122 4246.0305)
      (2345.8321 4249.8931) (2341.9542 4252.4733) (2337.4046 4253.3893) (2332.855 4252.4733) (2328.9771 4249.8931)
      (2326.3969 4246.0305)
    ))
    ; P2294 -- see feature_dimensions_mm.csv
    ("06_ORNAMENT" 1 (
      (2325.4962 3930.0305) (2326.3969 3925.4656) (2328.9771 3921.6031) (2332.855 3919.0229) (2337.4046 3918.1221)
      (2341.9542 3919.0229) (2345.8321 3921.6031) (2348.4122 3925.4656) (2349.313 3930.0305) (2348.4122 3934.5802)
      (2345.8321 3938.4427) (2341.9542 3941.0229) (2337.4046 3941.9389) (2332.855 3941.0229) (2328.9771 3938.4427)
      (2326.3969 3934.5802)
    ))
    ; P2295 -- see feature_dimensions_mm.csv
    ("06_ORNAMENT" 1 (
      (2334.7786 2110.4122) (2335.3282 2098.5649) (2337.374 2086.9466) (2341.0534 2075.6794) (2346.4733 2064.8855)
      (2356.7176 2072.1374) (2365.6947 2080.6107) (2373.4046 2090.1374) (2379.9084 2100.5344) (2385.2366 2111.6336)
      (2389.4198 2123.2214) (2392.5038 2135.145) (2394.5038 2147.2061) (2395.4809 2159.2214) (2395.4351 2171.0229)
      (2394.4427 2182.4275) (2392.5038 2193.2366) (2389.6794 2203.2672) (2385.9847 2212.3664) (2378.0153 2205.4809)
      (2370.3664 2197.5115) (2363.145 2188.5802) (2356.4733 2178.8397) (2350.4885 2168.4122) (2345.2824 2157.4046)
      (2340.9924 2145.9847) (2337.7405 2134.2595) (2335.6336 2122.3511)
    ))
    ; P2296 -- see feature_dimensions_mm.csv
    ("06_ORNAMENT" 1 (
      (2335.3435 1368.4275) (2336.2748 1356.1679) (2338.4427 1344.0305) (2341.7405 1332.1679) (2346.0305 1320.7176)
      (2351.2061 1309.8321) (2357.1298 1299.6183) (2363.6947 1290.2595) (2370.7786 1281.8626) (2378.2443 1274.5802)
      (2385.9847 1268.5496) (2389.4504 1278.5038) (2392.0916 1289.2366) (2393.8779 1300.5649) (2394.7786 1312.3359)
      (2394.7634 1324.3664) (2393.7557 1336.5038) (2391.7557 1348.5344) (2388.7176 1360.3206) (2384.5954 1371.6794)
      (2379.3588 1382.4427) (2372.9618 1392.4275) (2365.374 1401.4656) (2356.5649 1409.3893) (2346.4733 1416.0305)
      (2341.2214 1404.626) (2337.6947 1392.8092) (2335.771 1380.687)
    ))
    ; P2297 -- see feature_dimensions_mm.csv
    ("06_ORNAMENT" 1 (
      (2365.313 1801.5267) (2385.6183 1799.1756) (2406.0 1799.6031) (2426.2748 1802.5649) (2446.2748 1807.8015)
      (2465.8015 1815.084) (2484.6718 1824.1679) (2502.7176 1834.7786) (2519.7252 1846.6718) (2535.542 1859.6183)
      (2549.9695 1873.3588) (2562.8092 1887.6489) (2573.9084 1902.229) (2583.0534 1916.8702) (2590.0916 1931.2977)
      (2572.7634 1931.6794) (2554.4733 1930.458) (2535.4809 1927.6794) (2516.1221 1923.3588) (2496.6565 1917.542)
      (2477.374 1910.229) (2458.5954 1901.4504) (2440.5802 1891.2519) (2423.6489 1879.6641) (2408.0916 1866.6718)
      (2394.1679 1852.3511) (2382.2137 1836.7023) (2372.5038 1819.7405)
    ))
    ; P2298 -- see feature_dimensions_mm.csv
    ("06_ORNAMENT" 1 (
      (2365.313 1679.3893) (2373.4198 1660.6412) (2383.9847 1643.1908) (2396.687 1627.1145) (2411.2366 1612.4275)
      (2427.2977 1599.145) (2444.5954 1587.3435) (2462.8092 1577.0229) (2481.6183 1568.2443) (2500.7481 1561.0229)
      (2519.8473 1555.4046) (2538.6565 1551.4046) (2556.8244 1549.0992) (2574.0763 1548.4885) (2590.0916 1549.6183)
      (2581.7557 1564.8092) (2571.542 1580.0458) (2559.6489 1595.084) (2546.229 1609.7099) (2531.4504 1623.6489)
      (2515.4809 1636.687) (2498.5038 1648.5802) (2480.6565 1659.0687) (2462.1527 1667.9389) (2443.1298 1674.9313)
      (2423.7557 1679.8015) (2404.229 1682.3359) (2384.687 1682.2748)
    ))
    ; P2299 -- see feature_dimensions_mm.csv
    ("06_ORNAMENT" 1 (
      (2365.6489 5331.5573) (2367.3435 5328.4122) (2371.9695 5325.8626) (2378.2748 5324.1985) (2384.5954 5323.3282)
      (2389.3282 5322.7481) (2391.4351 5321.6794) (2390.7023 5319.4351) (2387.771 5315.6794) (2383.9084 5310.6107)
      (2380.626 5304.9771) (2379.1603 5299.8931) (2380.1832 5296.4733) (2383.6031 5295.4504) (2388.687 5296.916)
      (2394.3206 5300.1985) (2399.3893 5304.0458) (2403.145 5306.9771) (2405.3893 5307.7099) (2406.458 5305.6183)
      (2407.0534 5300.8855) (2407.9084 5294.5649) (2409.5725 5288.2595) (2412.1221 5283.6336) (2415.2672 5281.9389)
      (2418.4122 5283.6336) (2420.9618 5288.2595) (2422.626 5294.5649) (2423.4809 5300.8855) (2424.0763 5305.6183)
      (2425.145 5307.7099) (2427.3893 5306.9771) (2431.145 5304.0458) (2436.2137 5300.1985) (2441.8473 5296.916)
      (2446.9313 5295.4504) (2450.3511 5296.4733) (2451.374 5299.8931) (2449.9084 5304.9771) (2446.626 5310.6107)
      (2442.7634 5315.6794) (2439.8321 5319.4351) (2439.0992 5321.6794) (2441.2061 5322.7481) (2445.9389 5323.3282)
      (2452.2595 5324.1985) (2458.5649 5325.8626) (2463.1908 5328.4122) (2464.8855 5331.5573) (2463.1908 5334.7023)
      (2458.5649 5337.2519) (2452.2595 5338.916) (2445.9389 5339.771) (2441.2061 5340.3664) (2439.0992 5341.4351)
      (2439.8321 5343.6794) (2442.7634 5347.4351) (2446.626 5352.5038) (2449.9084 5358.1374) (2451.374 5363.2214)
      (2450.3511 5366.6412) (2446.9313 5367.6641) (2441.8473 5366.1985) (2436.2137 5362.916) (2431.145 5359.0534)
      (2427.3893 5356.1221) (2425.145 5355.3893) (2424.0763 5357.4962) (2423.4809 5362.229) (2422.626 5368.5344)
      (2420.9618 5374.8397) (2418.4122 5379.4809) (2415.2672 5381.1756) (2412.1221 5379.4809) (2409.5725 5374.8397)
      (2407.9084 5368.5344) (2407.0534 5362.229) (2406.458 5357.4962) (2405.3893 5355.3893) (2403.145 5356.1221)
      (2399.3893 5359.0534) (2394.3206 5362.916) (2388.687 5366.1985) (2383.6031 5367.6641) (2380.1832 5366.6412)
      (2379.1603 5363.2214) (2380.626 5358.1374) (2383.9084 5352.5038) (2387.771 5347.4351) (2390.7023 5343.6794)
      (2391.4351 5341.4351) (2389.3282 5340.3664) (2384.5954 5339.771) (2378.2748 5338.916) (2371.9695 5337.2519)
      (2367.3435 5334.7023)
    ))
    ; P2300 -- see feature_dimensions_mm.csv
    ("06_ORNAMENT" 1 (
      (2365.6489 5020.1069) (2367.3435 5016.9618) (2371.9695 5014.4122) (2378.2748 5012.7481) (2384.5954 5011.8779)
      (2389.3282 5011.2977) (2391.4351 5010.229) (2390.7023 5007.9847) (2387.771 5004.229) (2383.9084 4999.1603)
      (2380.626 4993.5267) (2379.1603 4988.4427) (2380.1832 4985.0229) (2383.6031 4984.0) (2388.687 4985.4656)
      (2394.3206 4988.7481) (2399.3893 4992.5954) (2403.145 4995.5267) (2405.3893 4996.2595) (2406.458 4994.1679)
      (2407.0534 4989.4351) (2407.9084 4983.1145) (2409.5725 4976.8092) (2412.1221 4972.1832) (2415.2672 4970.4885)
      (2418.4122 4972.1832) (2420.9618 4976.8092) (2422.626 4983.1145) (2423.4809 4989.4351) (2424.0763 4994.1679)
      (2425.145 4996.2595) (2427.3893 4995.5267) (2431.145 4992.5954) (2436.2137 4988.7481) (2441.8473 4985.4656)
      (2446.9313 4984.0) (2450.3511 4985.0229) (2451.374 4988.4427) (2449.9084 4993.5267) (2446.626 4999.1603)
      (2442.7634 5004.229) (2439.8321 5007.9847) (2439.0992 5010.229) (2441.2061 5011.2977) (2445.9389 5011.8779)
      (2452.2595 5012.7481) (2458.5649 5014.4122) (2463.1908 5016.9618) (2464.8855 5020.1069) (2463.1908 5023.2519)
      (2458.5649 5025.8015) (2452.2595 5027.4656) (2445.9389 5028.3206) (2441.2061 5028.916) (2439.0992 5029.9847)
      (2439.8321 5032.229) (2442.7634 5035.9847) (2446.626 5041.0534) (2449.9084 5046.687) (2451.374 5051.771)
      (2450.3511 5055.1908) (2446.9313 5056.2137) (2441.8473 5054.7481) (2436.2137 5051.4656) (2431.145 5047.6031)
      (2427.3893 5044.6718) (2425.145 5043.9389) (2424.0763 5046.0458) (2423.4809 5050.7786) (2422.626 5057.084)
      (2420.9618 5063.3893) (2418.4122 5068.0305) (2415.2672 5069.7252) (2412.1221 5068.0305) (2409.5725 5063.3893)
      (2407.9084 5057.084) (2407.0534 5050.7786) (2406.458 5046.0458) (2405.3893 5043.9389) (2403.145 5044.6718)
      (2399.3893 5047.6031) (2394.3206 5051.4656) (2388.687 5054.7481) (2383.6031 5056.2137) (2380.1832 5055.1908)
      (2379.1603 5051.771) (2380.626 5046.687) (2383.9084 5041.0534) (2387.771 5035.9847) (2390.7023 5032.229)
      (2391.4351 5029.9847) (2389.3282 5028.916) (2384.5954 5028.3206) (2378.2748 5027.4656) (2371.9695 5025.8015)
      (2367.3435 5023.2519)
    ))
    ; P2301 -- see feature_dimensions_mm.csv
    ("06_ORNAMENT" 1 (
      (2365.6489 4708.6565) (2367.3435 4705.5115) (2371.9695 4702.9618) (2378.2748 4701.2977) (2384.5954 4700.4275)
      (2389.3282 4699.8473) (2391.4351 4698.7786) (2390.7023 4696.5344) (2387.771 4692.7786) (2383.9084 4687.7099)
      (2380.626 4682.0763) (2379.1603 4676.9924) (2380.1832 4673.5725) (2383.6031 4672.5496) (2388.687 4674.0153)
      (2394.3206 4677.2977) (2399.3893 4681.145) (2403.145 4684.0763) (2405.3893 4684.8092) (2406.458 4682.7176)
      (2407.0534 4677.9847) (2407.9084 4671.6641) (2409.5725 4665.3588) (2412.1221 4660.7328) (2415.2672 4659.0382)
      (2418.4122 4660.7328) (2420.9618 4665.3588) (2422.626 4671.6641) (2423.4809 4677.9847) (2424.0763 4682.7176)
      (2425.145 4684.8092) (2427.3893 4684.0763) (2431.145 4681.145) (2436.2137 4677.2977) (2441.8473 4674.0153)
      (2446.9313 4672.5496) (2450.3511 4673.5725) (2451.374 4676.9924) (2449.9084 4682.0763) (2446.626 4687.7099)
      (2442.7634 4692.7786) (2439.8321 4696.5344) (2439.0992 4698.7786) (2441.2061 4699.8473) (2445.9389 4700.4275)
      (2452.2595 4701.2977) (2458.5649 4702.9618) (2463.1908 4705.5115) (2464.8855 4708.6565) (2463.1908 4711.8015)
      (2458.5649 4714.3511) (2452.2595 4716.0153) (2445.9389 4716.8702) (2441.2061 4717.4656) (2439.0992 4718.5344)
      (2439.8321 4720.7786) (2442.7634 4724.5344) (2446.626 4729.6031) (2449.9084 4735.2366) (2451.374 4740.3206)
      (2450.3511 4743.7405) (2446.9313 4744.7634) (2441.8473 4743.2977) (2436.2137 4740.0153) (2431.145 4736.1527)
      (2427.3893 4733.2214) (2425.145 4732.4885) (2424.0763 4734.5954) (2423.4809 4739.3282) (2422.626 4745.6336)
      (2420.9618 4751.9389) (2418.4122 4756.5802) (2415.2672 4758.2748) (2412.1221 4756.5802) (2409.5725 4751.9389)
      (2407.9084 4745.6336) (2407.0534 4739.3282) (2406.458 4734.5954) (2405.3893 4732.4885) (2403.145 4733.2214)
      (2399.3893 4736.1527) (2394.3206 4740.0153) (2388.687 4743.2977) (2383.6031 4744.7634) (2380.1832 4743.7405)
      (2379.1603 4740.3206) (2380.626 4735.2366) (2383.9084 4729.6031) (2387.771 4724.5344) (2390.7023 4720.7786)
      (2391.4351 4718.5344) (2389.3282 4717.4656) (2384.5954 4716.8702) (2378.2748 4716.0153) (2371.9695 4714.3511)
      (2367.3435 4711.8015)
    ))
    ; P2302 -- see feature_dimensions_mm.csv
    ("06_ORNAMENT" 1 (
      (2365.6489 4397.2061) (2367.3435 4394.0611) (2371.9695 4391.5115) (2378.2748 4389.8473) (2384.5954 4388.9771)
      (2389.3282 4388.3969) (2391.4351 4387.3282) (2390.7023 4385.084) (2387.771 4381.3282) (2383.9084 4376.2595)
      (2380.626 4370.626) (2379.1603 4365.542) (2380.1832 4362.1221) (2383.6031 4361.0992) (2388.687 4362.5649)
      (2394.3206 4365.8473) (2399.3893 4369.6947) (2403.145 4372.626) (2405.3893 4373.3588) (2406.458 4371.2672)
      (2407.0534 4366.5344) (2407.9084 4360.2137) (2409.5725 4353.9084) (2412.1221 4349.2824) (2415.2672 4347.5878)
      (2418.4122 4349.2824) (2420.9618 4353.9084) (2422.626 4360.2137) (2423.4809 4366.5344) (2424.0763 4371.2672)
      (2425.145 4373.3588) (2427.3893 4372.626) (2431.145 4369.6947) (2436.2137 4365.8473) (2441.8473 4362.5649)
      (2446.9313 4361.0992) (2450.3511 4362.1221) (2451.374 4365.542) (2449.9084 4370.626) (2446.626 4376.2595)
      (2442.7634 4381.3282) (2439.8321 4385.084) (2439.0992 4387.3282) (2441.2061 4388.3969) (2445.9389 4388.9771)
      (2452.2595 4389.8473) (2458.5649 4391.5115) (2463.1908 4394.0611) (2464.8855 4397.2061) (2463.1908 4400.3511)
      (2458.5649 4402.9008) (2452.2595 4404.5649) (2445.9389 4405.4198) (2441.2061 4406.0153) (2439.0992 4407.084)
      (2439.8321 4409.3282) (2442.0916 4412.2137) (2388.4427 4412.2137) (2390.7023 4409.3282) (2391.4351 4407.084)
      (2389.3282 4406.0153) (2384.5954 4405.4198) (2378.2748 4404.5649) (2371.9695 4402.9008) (2367.3435 4400.3511)
    ))
    ; P2303 -- see feature_dimensions_mm.csv
    ("06_ORNAMENT" 1 (
      (2365.6489 4085.7557) (2367.3435 4082.6107) (2371.9695 4080.0611) (2378.2748 4078.3969) (2384.5954 4077.5267)
      (2389.3282 4076.9466) (2391.4351 4075.8779) (2390.7023 4073.6336) (2387.771 4069.8779) (2383.9084 4064.8092)
      (2380.626 4059.1756) (2379.1603 4054.0916) (2380.1832 4050.6718) (2383.6031 4049.6489) (2388.687 4051.1145)
      (2394.3206 4054.3969) (2399.3893 4058.2595) (2403.145 4061.1756) (2405.3893 4061.9084) (2406.458 4059.8168)
      (2407.0534 4055.084) (2407.9084 4048.7634) (2409.5725 4042.458) (2412.1221 4037.8321) (2415.2672 4036.1374)
      (2418.4122 4037.8321) (2420.9618 4042.458) (2422.626 4048.7634) (2423.4809 4055.084) (2424.0763 4059.8168)
      (2425.145 4061.9084) (2427.3893 4061.1756) (2431.145 4058.2595) (2436.2137 4054.3969) (2441.8473 4051.1145)
      (2446.9313 4049.6489) (2450.3511 4050.6718) (2451.374 4054.0916) (2449.9084 4059.1756) (2446.626 4064.8092)
      (2442.7634 4069.8779) (2439.8321 4073.6336) (2439.0992 4075.8779) (2441.2061 4076.9466) (2445.9389 4077.5267)
      (2452.2595 4078.3969) (2458.5649 4080.0611) (2463.1908 4082.6107) (2464.8855 4085.7557) (2463.1908 4088.9008)
      (2458.5649 4091.4504) (2452.2595 4093.1145) (2445.9389 4093.9695) (2441.2061 4094.5649) (2439.0992 4095.6336)
      (2439.8321 4097.8779) (2442.7634 4101.6336) (2446.626 4106.7023) (2449.9084 4112.3359) (2451.374 4117.4198)
      (2450.3511 4120.8397) (2446.9313 4121.8626) (2441.8473 4120.3969) (2436.2137 4117.1145) (2431.145 4113.2519)
      (2427.3893 4110.3206) (2425.145 4109.5878) (2424.0763 4111.6947) (2423.4809 4116.4275) (2422.626 4122.7328)
      (2420.9618 4129.0382) (2418.4122 4133.6794) (2415.2672 4135.374) (2412.1221 4133.6794) (2409.5725 4129.0382)
      (2407.9084 4122.7328) (2407.0534 4116.4275) (2406.458 4111.6947) (2405.3893 4109.5878) (2403.145 4110.3206)
      (2399.3893 4113.2519) (2394.3206 4117.1145) (2388.687 4120.3969) (2383.6031 4121.8626) (2380.1832 4120.8397)
      (2379.1603 4117.4198) (2380.626 4112.3359) (2383.9084 4106.7023) (2387.771 4101.6336) (2390.7023 4097.8779)
      (2391.4351 4095.6336) (2389.3282 4094.5649) (2384.5954 4093.9695) (2378.2748 4093.1145) (2371.9695 4091.4504)
      (2367.3435 4088.9008)
    ))
    ; P2304 -- see feature_dimensions_mm.csv
    ("06_ORNAMENT" 1 (
      (2381.6794 6000.0) (2383.9237 5985.8473) (2390.4275 5973.084) (2400.5649 5962.9466) (2413.3282 5956.4427)
      (2427.4809 5954.1985) (2441.6336 5956.4427) (2454.3969 5962.9466) (2464.5344 5973.084) (2471.0382 5985.8473)
      (2473.2824 6000.0) (2471.0382 6014.1527) (2464.5344 6026.916) (2454.3969 6037.0534) (2441.6336 6043.5573)
      (2427.4809 6045.8015) (2413.3282 6043.5573) (2400.5649 6037.0534) (2390.4275 6026.916) (2383.9237 6014.1527)
    ))
    ; P2305 -- see feature_dimensions_mm.csv
    ("06_ORNAMENT" 1 (
      (2381.6794 1740.458) (2398.0763 1728.2748) (2415.9389 1718.4427) (2434.9924 1710.8702) (2454.9313 1705.4198)
      (2475.4809 1701.9695) (2496.3664 1700.3817) (2517.2977 1700.5496) (2537.9847 1702.3511) (2558.1527 1705.6641)
      (2577.5115 1710.3511) (2595.7863 1716.2901) (2612.687 1723.374) (2627.9237 1731.4656) (2641.2214 1740.458)
      (2626.4122 1749.4504) (2609.9542 1757.542) (2592.1221 1764.626) (2573.1908 1770.5649) (2553.4198 1775.2519)
      (2533.084 1778.5649) (2512.4275 1780.3664) (2491.7252 1780.5344) (2471.2672 1778.9466) (2451.2977 1775.4962)
      (2432.0763 1770.0458) (2413.8931 1762.4733) (2397.0076 1752.6412)
    ))
    ; P2306 -- see feature_dimensions_mm.csv
    ("06_ORNAMENT" 1 (
      (2396.9466 5097.9695) (2415.2672 5077.3588) (2433.5878 5097.9695) (2415.2672 5118.5802)
    ))
    ; P2307 -- see feature_dimensions_mm.csv
    ("06_ORNAMENT" 1 (
      (2396.9466 4786.5191) (2415.2672 4765.9084) (2433.5878 4786.5191) (2415.2672 4807.1298)
    ))
    ; P2308 -- see feature_dimensions_mm.csv
    ("06_ORNAMENT" 1 (
      (2396.9466 4163.6183) (2415.2672 4143.0076) (2433.5878 4163.6183) (2415.2672 4184.229)
    ))
    ; P2309 -- see feature_dimensions_mm.csv
    ("06_ORNAMENT" 1 (
      (2403.3588 5331.5573) (2404.2595 5326.9924) (2406.8397 5323.1298) (2410.7176 5320.5496) (2415.2672 5319.6489)
      (2419.8168 5320.5496) (2423.6947 5323.1298) (2426.2748 5326.9924) (2427.1756 5331.5573) (2426.2748 5336.1069)
      (2423.6947 5339.9695) (2419.8168 5342.5496) (2415.2672 5343.4656) (2410.7176 5342.5496) (2406.8397 5339.9695)
      (2404.2595 5336.1069)
    ))
    ; P2310 -- see feature_dimensions_mm.csv
    ("06_ORNAMENT" 1 (
      (2403.3588 5020.1069) (2404.2595 5015.542) (2406.8397 5011.6794) (2410.7176 5009.0992) (2415.2672 5008.1985)
      (2419.8168 5009.0992) (2423.6947 5011.6794) (2426.2748 5015.542) (2427.1756 5020.1069) (2426.2748 5024.6565)
      (2423.6947 5028.5191) (2419.8168 5031.0992) (2415.2672 5032.0153) (2410.7176 5031.0992) (2406.8397 5028.5191)
      (2404.2595 5024.6565)
    ))
    ; P2311 -- see feature_dimensions_mm.csv
    ("06_ORNAMENT" 1 (
      (2403.3588 4708.6565) (2404.2595 4704.0916) (2406.8397 4700.229) (2410.7176 4697.6489) (2415.2672 4696.7481)
      (2419.8168 4697.6489) (2423.6947 4700.229) (2426.2748 4704.0916) (2427.1756 4708.6565) (2426.2748 4713.2061)
      (2423.6947 4717.0687) (2419.8168 4719.6489) (2415.2672 4720.5649) (2410.7176 4719.6489) (2406.8397 4717.0687)
      (2404.2595 4713.2061)
    ))
    ; P2312 -- see feature_dimensions_mm.csv
    ("06_ORNAMENT" 1 (
      (2403.3588 4397.2061) (2404.2595 4392.6412) (2406.8397 4388.7786) (2410.7176 4386.1985) (2415.2672 4385.2977)
      (2419.8168 4386.1985) (2423.6947 4388.7786) (2426.2748 4392.6412) (2427.1756 4397.2061) (2426.2748 4401.7557)
      (2423.6947 4405.6183) (2419.8168 4408.1985) (2415.2672 4409.1145) (2410.7176 4408.1985) (2406.8397 4405.6183)
      (2404.2595 4401.7557)
    ))
    ; P2313 -- see feature_dimensions_mm.csv
    ("06_ORNAMENT" 1 (
      (2403.3588 4085.7557) (2404.2595 4081.1908) (2406.8397 4077.3282) (2410.7176 4074.7481) (2415.2672 4073.8473)
      (2419.8168 4074.7481) (2423.6947 4077.3282) (2426.2748 4081.1908) (2427.1756 4085.7557) (2426.2748 4090.3053)
      (2423.6947 4094.1679) (2419.8168 4096.7481) (2415.2672 4097.6641) (2410.7176 4096.7481) (2406.8397 4094.1679)
      (2404.2595 4090.3053)
    ))
    ; P2314 -- see feature_dimensions_mm.csv
    ("06_ORNAMENT" 1 (
      (2443.5115 5175.8321) (2445.2061 5172.687) (2449.8321 5170.1374) (2456.1374 5168.4733) (2462.458 5167.6031)
      (2467.1908 5167.0229) (2469.2977 5165.9542) (2468.5649 5163.7099) (2465.6336 5159.9542) (2461.771 5154.8855)
      (2458.4885 5149.2519) (2457.0229 5144.1679) (2458.0458 5140.7481) (2461.4656 5139.7252) (2466.5496 5141.1908)
      (2472.1832 5144.4733) (2477.2519 5148.3206) (2481.0076 5151.2519) (2483.2519 5151.9847) (2484.3206 5149.8931)
      (2484.916 5145.1603) (2485.771 5138.8397) (2487.4351 5132.5344) (2489.9847 5127.9084) (2493.1298 5126.2137)
      (2496.2748 5127.9084) (2498.8244 5132.5344) (2500.4885 5138.8397) (2501.3435 5145.1603) (2501.9389 5149.8931)
      (2503.0076 5151.9847) (2505.2519 5151.2519) (2509.0076 5148.3206) (2514.0763 5144.4733) (2519.7099 5141.1908)
      (2524.7939 5139.7252) (2528.2137 5140.7481) (2529.2366 5144.1679) (2527.771 5149.2519) (2524.4885 5154.8855)
      (2520.626 5159.9542) (2517.6947 5163.7099) (2516.9618 5165.9542) (2519.0687 5167.0229) (2523.8015 5167.6031)
      (2530.1221 5168.4733) (2536.4275 5170.1374) (2541.0534 5172.687) (2542.7481 5175.8321) (2541.0534 5178.9771)
      (2536.4275 5181.5267) (2530.1221 5183.1908) (2523.8015 5184.0458) (2519.0687 5184.6412) (2516.9618 5185.7099)
      (2517.6947 5187.9542) (2520.626 5191.7099) (2524.4885 5196.7786) (2527.771 5202.4122) (2529.2366 5207.4962)
      (2528.2137 5210.916) (2524.7939 5211.9389) (2519.7099 5210.4733) (2514.0763 5207.1908) (2509.0076 5203.3282)
      (2505.2519 5200.3969) (2503.0076 5199.6641) (2501.9389 5201.771) (2501.3435 5206.5038) (2500.4885 5212.8092)
      (2498.8244 5219.1145) (2496.2748 5223.7557) (2493.1298 5225.4504) (2489.9847 5223.7557) (2487.4351 5219.1145)
      (2485.771 5212.8092) (2484.916 5206.5038) (2484.3206 5201.771) (2483.2519 5199.6641) (2481.0076 5200.3969)
      (2477.2519 5203.3282) (2472.1832 5207.1908) (2466.5496 5210.4733) (2461.4656 5211.9389) (2458.0458 5210.916)
      (2457.0229 5207.4962) (2458.4885 5202.4122) (2461.771 5196.7786) (2465.6336 5191.7099) (2468.5649 5187.9542)
      (2469.2977 5185.7099) (2467.1908 5184.6412) (2462.458 5184.0458) (2456.1374 5183.1908) (2449.8321 5181.5267)
      (2445.2061 5178.9771)
    ))
    ; P2315 -- see feature_dimensions_mm.csv
    ("06_ORNAMENT" 1 (
      (2443.5115 4864.3817) (2445.2061 4861.2366) (2449.8321 4858.687) (2456.1374 4857.0229) (2462.458 4856.1527)
      (2467.1908 4855.5725) (2469.2977 4854.5038) (2468.5649 4852.2595) (2465.6336 4848.5038) (2461.771 4843.4351)
      (2458.4885 4837.8015) (2457.0229 4832.7176) (2458.0458 4829.2977) (2461.4656 4828.2748) (2466.5496 4829.7405)
      (2472.1832 4833.0229) (2477.2519 4836.8702) (2481.0076 4839.8015) (2483.2519 4840.5344) (2484.3206 4838.4427)
      (2484.916 4833.7099) (2485.771 4827.3893) (2487.4351 4821.084) (2489.9847 4816.458) (2493.1298 4814.7634)
      (2496.2748 4816.458) (2498.8244 4821.084) (2500.4885 4827.3893) (2501.3435 4833.7099) (2501.9389 4838.4427)
      (2503.0076 4840.5344) (2505.2519 4839.8015) (2509.0076 4836.8702) (2514.0763 4833.0229) (2519.7099 4829.7405)
      (2524.7939 4828.2748) (2528.2137 4829.2977) (2529.2366 4832.7176) (2527.771 4837.8015) (2524.4885 4843.4351)
      (2520.626 4848.5038) (2517.6947 4852.2595) (2516.9618 4854.5038) (2519.0687 4855.5725) (2523.8015 4856.1527)
      (2530.1221 4857.0229) (2536.4275 4858.687) (2541.0534 4861.2366) (2542.7481 4864.3817) (2541.0534 4867.5267)
      (2536.4275 4870.0763) (2530.1221 4871.7405) (2523.8015 4872.5954) (2519.0687 4873.1908) (2516.9618 4874.2595)
      (2517.6947 4876.5038) (2520.626 4880.2595) (2524.4885 4885.3282) (2527.771 4890.9618) (2529.2366 4896.0458)
      (2528.2137 4899.4656) (2524.7939 4900.4885) (2519.7099 4899.0229) (2514.0763 4895.7405) (2509.0076 4891.8779)
      (2505.2519 4888.9466) (2503.0076 4888.2137) (2501.9389 4890.3206) (2501.3435 4895.0534) (2500.4885 4901.3588)
      (2498.8244 4907.6641) (2496.2748 4912.3053) (2493.1298 4914.0) (2489.9847 4912.3053) (2487.4351 4907.6641)
      (2485.771 4901.3588) (2484.916 4895.0534) (2484.3206 4890.3206) (2483.2519 4888.2137) (2481.0076 4888.9466)
      (2477.2519 4891.8779) (2472.1832 4895.7405) (2466.5496 4899.0229) (2461.4656 4900.4885) (2458.0458 4899.4656)
      (2457.0229 4896.0458) (2458.4885 4890.9618) (2461.771 4885.3282) (2465.6336 4880.2595) (2468.5649 4876.5038)
      (2469.2977 4874.2595) (2467.1908 4873.1908) (2462.458 4872.5954) (2456.1374 4871.7405) (2449.8321 4870.0763)
      (2445.2061 4867.5267)
    ))
    ; P2316 -- see feature_dimensions_mm.csv
    ("06_ORNAMENT" 1 (
      (2443.5115 4552.9313) (2445.2061 4549.7863) (2449.8321 4547.2366) (2456.1374 4545.5725) (2462.458 4544.7023)
      (2467.1908 4544.1221) (2469.2977 4543.0534) (2468.5649 4540.8092) (2465.6336 4537.0534) (2461.771 4531.9847)
      (2458.4885 4526.3511) (2457.0229 4521.2672) (2458.0458 4517.8473) (2461.4656 4516.8244) (2466.5496 4518.2901)
      (2472.1832 4521.5725) (2477.2519 4525.4198) (2481.0076 4528.3511) (2483.2519 4529.084) (2484.3206 4526.9924)
      (2484.916 4522.2595) (2485.771 4515.9389) (2487.4351 4509.6336) (2489.9847 4505.0076) (2493.1298 4503.313)
      (2496.2748 4505.0076) (2498.8244 4509.6336) (2500.4885 4515.9389) (2501.3435 4522.2595) (2501.9389 4526.9924)
      (2503.0076 4529.084) (2505.2519 4528.3511) (2509.0076 4525.4198) (2514.0763 4521.5725) (2519.7099 4518.2901)
      (2524.7939 4516.8244) (2528.2137 4517.8473) (2529.2366 4521.2672) (2527.771 4526.3511) (2524.4885 4531.9847)
      (2520.626 4537.0534) (2517.6947 4540.8092) (2516.9618 4543.0534) (2519.0687 4544.1221) (2523.8015 4544.7023)
      (2530.1221 4545.5725) (2536.4275 4547.2366) (2541.0534 4549.7863) (2542.7481 4552.9313) (2541.0534 4556.0763)
      (2536.4275 4558.626) (2530.1221 4560.2901) (2523.8015 4561.145) (2519.0687 4561.7405) (2516.9618 4562.8092)
      (2517.6947 4565.0534) (2520.626 4568.8092) (2524.4885 4573.8779) (2527.771 4579.5115) (2529.2366 4584.5954)
      (2528.2137 4588.0153) (2524.7939 4589.0382) (2519.7099 4587.5725) (2514.0763 4584.2901) (2509.0076 4580.4275)
      (2505.2519 4577.4962) (2503.0076 4576.7634) (2501.9389 4578.8702) (2501.3435 4583.6031) (2500.4885 4589.9084)
      (2498.8244 4596.2137) (2496.2748 4600.855) (2493.1298 4602.5496) (2489.9847 4600.855) (2487.4351 4596.2137)
      (2485.771 4589.9084) (2484.916 4583.6031) (2484.3206 4578.8702) (2483.2519 4576.7634) (2481.0076 4577.4962)
      (2477.2519 4580.4275) (2472.1832 4584.2901) (2466.5496 4587.5725) (2461.4656 4589.0382) (2458.0458 4588.0153)
      (2457.0229 4584.5954) (2458.4885 4579.5115) (2461.771 4573.8779) (2465.6336 4568.8092) (2468.5649 4565.0534)
      (2469.2977 4562.8092) (2467.1908 4561.7405) (2462.458 4561.145) (2456.1374 4560.2901) (2449.8321 4558.626)
      (2445.2061 4556.0763)
    ))
    ; P2317 -- see feature_dimensions_mm.csv
    ("06_ORNAMENT" 1 (
      (2443.5115 4241.4809) (2445.2061 4238.3359) (2449.8321 4235.7863) (2456.1374 4234.1221) (2462.458 4233.2519)
      (2467.1908 4232.6718) (2469.2977 4231.6031) (2468.5649 4229.3588) (2465.6336 4225.6031) (2461.771 4220.5344)
      (2458.4885 4214.9008) (2457.0229 4209.8168) (2458.0458 4206.3969) (2461.4656 4205.374) (2466.5496 4206.8397)
      (2472.1832 4210.1221) (2477.2519 4213.9695) (2481.0076 4216.9008) (2483.2519 4217.6336) (2484.3206 4215.542)
      (2484.916 4210.8092) (2485.771 4204.4885) (2487.4351 4198.1832) (2489.9847 4193.5573) (2493.1298 4191.8626)
      (2496.2748 4193.5573) (2498.8244 4198.1832) (2500.4885 4204.4885) (2501.3435 4210.8092) (2501.9389 4215.542)
      (2503.0076 4217.6336) (2505.2519 4216.9008) (2509.0076 4213.9695) (2514.0763 4210.1221) (2519.7099 4206.8397)
      (2524.7939 4205.374) (2528.2137 4206.3969) (2529.2366 4209.8168) (2527.771 4214.9008) (2524.4885 4220.5344)
      (2520.626 4225.6031) (2517.6947 4229.3588) (2516.9618 4231.6031) (2519.0687 4232.6718) (2523.8015 4233.2519)
      (2530.1221 4234.1221) (2536.4275 4235.7863) (2541.0534 4238.3359) (2542.7481 4241.4809) (2541.0534 4244.626)
      (2536.4275 4247.1756) (2530.1221 4248.8397) (2523.8015 4249.6947) (2519.0687 4250.2901) (2516.9618 4251.3588)
      (2517.6947 4253.6031) (2520.626 4257.3588) (2524.4885 4262.4275) (2527.771 4268.0611) (2529.2366 4273.145)
      (2528.2137 4276.5649) (2524.7939 4277.5878) (2519.7099 4276.1221) (2514.0763 4272.8397) (2509.0076 4268.9771)
      (2505.2519 4266.0458) (2503.0076 4265.313) (2501.9389 4267.4198) (2501.3435 4272.1527) (2500.4885 4278.458)
      (2498.8244 4284.7634) (2496.2748 4289.4046) (2493.1298 4291.0992) (2489.9847 4289.4046) (2487.4351 4284.7634)
      (2485.771 4278.458) (2484.916 4272.1527) (2484.3206 4267.4198) (2483.2519 4265.313) (2481.0076 4266.0458)
      (2477.2519 4268.9771) (2472.1832 4272.8397) (2466.5496 4276.1221) (2461.4656 4277.5878) (2458.0458 4276.5649)
      (2457.0229 4273.145) (2458.4885 4268.0611) (2461.771 4262.4275) (2465.6336 4257.3588) (2468.5649 4253.6031)
      (2469.2977 4251.3588) (2467.1908 4250.2901) (2462.458 4249.6947) (2456.1374 4248.8397) (2449.8321 4247.1756)
      (2445.2061 4244.626)
    ))
    ; P2318 -- see feature_dimensions_mm.csv
    ("06_ORNAMENT" 1 (
      (2443.5115 3930.0305) (2445.2061 3926.8855) (2449.8321 3924.3359) (2456.1374 3922.6718) (2462.458 3921.8015)
      (2467.1908 3921.2214) (2469.2977 3920.1527) (2468.5649 3917.9084) (2465.6336 3914.1527) (2461.771 3909.084)
      (2458.4885 3903.4504) (2457.0229 3898.3664) (2458.0458 3894.9466) (2461.4656 3893.9237) (2466.5496 3895.3893)
      (2472.1832 3898.6718) (2477.2519 3902.5191) (2481.0076 3905.4504) (2483.2519 3906.1832) (2484.3206 3904.0916)
      (2484.916 3899.3588) (2485.771 3893.0382) (2487.4351 3886.7328) (2489.9847 3882.1069) (2493.1298 3880.4122)
      (2496.2748 3882.1069) (2498.8244 3886.7328) (2500.4885 3893.0382) (2501.3435 3899.3588) (2501.9389 3904.0916)
      (2503.0076 3906.1832) (2505.2519 3905.4504) (2509.0076 3902.5191) (2514.0763 3898.6718) (2519.7099 3895.3893)
      (2524.7939 3893.9237) (2528.2137 3894.9466) (2529.2366 3898.3664) (2527.771 3903.4504) (2524.4885 3909.084)
      (2520.626 3914.1527) (2517.6947 3917.9084) (2516.9618 3920.1527) (2519.0687 3921.2214) (2523.8015 3921.8015)
      (2530.1221 3922.6718) (2536.4275 3924.3359) (2541.0534 3926.8855) (2542.7481 3930.0305) (2541.0534 3933.1756)
      (2536.4275 3935.7252) (2530.1221 3937.3893) (2523.8015 3938.2443) (2519.0687 3938.8397) (2516.9618 3939.9084)
      (2517.6947 3942.1527) (2520.626 3945.9084) (2524.4885 3950.9771) (2527.771 3956.6107) (2529.2366 3961.6947)
      (2528.2137 3965.1145) (2524.7939 3966.1374) (2519.7099 3964.6718) (2514.0763 3961.3893) (2509.0076 3957.5267)
      (2505.2519 3954.5954) (2503.0076 3953.8626) (2501.9389 3955.9695) (2501.3435 3960.7023) (2500.4885 3967.0076)
      (2498.8244 3973.313) (2496.2748 3977.9542) (2493.1298 3979.6489) (2489.9847 3977.9542) (2487.4351 3973.313)
      (2485.771 3967.0076) (2484.916 3960.7023) (2484.3206 3955.9695) (2483.2519 3953.8626) (2481.0076 3954.5954)
      (2477.2519 3957.5267) (2472.1832 3961.3893) (2466.5496 3964.6718) (2461.4656 3966.1374) (2458.0458 3965.1145)
      (2457.0229 3961.6947) (2458.4885 3956.6107) (2461.771 3950.9771) (2465.6336 3945.9084) (2468.5649 3942.1527)
      (2469.2977 3939.9084) (2467.1908 3938.8397) (2462.458 3938.2443) (2456.1374 3937.3893) (2449.8321 3935.7252)
      (2445.2061 3933.1756)
    ))
    ; P2319 -- see feature_dimensions_mm.csv
    ("06_ORNAMENT" 1 (
      (2458.0153 2137.4046) (2459.2519 2133.4809) (2462.7939 2130.0) (2468.0611 2127.2519) (2474.2595 2125.3893)
      (2480.4427 2124.2901) (2485.7863 2123.6031) (2489.6031 2122.8702) (2491.5878 2121.5267) (2491.7557 2119.145)
      (2490.4885 2115.4656) (2488.4122 2110.5038) (2486.2595 2104.5802) (2484.7786 2098.2901) (2484.5191 2092.3664)
      (2485.771 2087.5573) (2488.5496 2084.5191) (2492.5649 2083.6336) (2497.3588 2084.9466) (2502.3664 2088.1374)
      (2507.0687 2092.5802) (2511.1298 2097.3893) (2514.3817 2101.6641) (2516.9313 2104.6107) (2519.084 2105.6489)
      (2521.2366 2104.6107) (2523.7863 2101.6641) (2527.0382 2097.3893) (2531.0992 2092.5802) (2535.8015 2088.1374)
      (2540.8092 2084.9466) (2545.6031 2083.6336) (2549.6183 2084.5191) (2552.3969 2087.5573) (2553.6489 2092.3664)
      (2553.3893 2098.2901) (2551.9084 2104.5802) (2549.7557 2110.5038) (2547.6794 2115.4656) (2546.4122 2119.145)
      (2546.5802 2121.5267) (2548.5649 2122.8702) (2552.3817 2123.6031) (2557.7252 2124.2901) (2563.9084 2125.3893)
      (2570.1069 2127.2519) (2575.374 2130.0) (2578.916 2133.4809) (2580.1527 2137.4046) (2578.916 2141.3282)
      (2575.374 2144.8092) (2570.1069 2147.5573) (2563.9084 2149.4198) (2557.7252 2150.5191) (2552.3817 2151.2061)
      (2548.5649 2151.9389) (2546.5802 2153.2824) (2546.4122 2155.6641) (2547.6794 2159.3435) (2549.7557 2164.3053)
      (2551.9084 2170.229) (2552.9313 2174.5954) (2538.3664 2185.8473) (2536.4885 2187.0992) (2535.8015 2186.6718)
      (2531.0992 2182.229) (2527.0382 2177.4198) (2523.7863 2173.145) (2521.2366 2170.1985) (2519.084 2169.1603)
      (2516.9313 2170.1985) (2514.3817 2173.145) (2511.1298 2177.4198) (2507.0687 2182.229) (2502.3664 2186.6718)
      (2497.3588 2189.8626) (2492.5649 2191.1756) (2488.5496 2190.2901) (2485.771 2187.2519) (2484.5191 2182.4427)
      (2484.7786 2176.5191) (2486.2595 2170.229) (2488.4122 2164.3053) (2490.4885 2159.3435) (2491.7557 2155.6641)
      (2491.5878 2153.2824) (2489.6031 2151.9389) (2485.7863 2151.2061) (2480.4427 2150.5191) (2474.2595 2149.4198)
      (2468.0611 2147.5573) (2462.7939 2144.8092) (2459.2519 2141.3282)
    ))
    ; P2320 -- see feature_dimensions_mm.csv
    ("06_ORNAMENT" 1 (
      (2458.0153 1374.0458) (2459.2519 1370.1221) (2462.7939 1366.6412) (2468.0611 1363.8931) (2474.2595 1362.0305)
      (2480.4427 1360.9313) (2485.7863 1360.2443) (2489.6031 1359.5115) (2491.5878 1358.1679) (2491.7557 1355.7863)
      (2490.4885 1352.1069) (2488.4122 1347.145) (2486.2595 1341.2214) (2484.7786 1334.9313) (2484.5191 1329.0076)
      (2485.771 1324.1985) (2488.5496 1321.1603) (2492.5649 1320.2748) (2497.3588 1321.5878) (2502.3664 1324.7786)
      (2507.0687 1329.2214) (2511.1298 1334.0305) (2514.3817 1338.3053) (2516.9313 1341.2519) (2519.084 1342.2901)
      (2521.2366 1341.2519) (2523.7863 1338.3053) (2527.0382 1334.0305) (2531.0992 1329.2214) (2535.8015 1324.7786)
      (2540.8092 1321.5878) (2545.6031 1320.2748) (2549.6183 1321.1603) (2552.3969 1324.1985) (2553.6489 1329.0076)
      (2553.3893 1334.9313) (2551.9084 1341.2214) (2549.7557 1347.145) (2547.6794 1352.1069) (2546.4122 1355.7863)
      (2546.5802 1358.1679) (2548.5649 1359.5115) (2552.3817 1360.2443) (2557.7252 1360.9313) (2563.9084 1362.0305)
      (2570.1069 1363.8931) (2575.374 1366.6412) (2578.916 1370.1221) (2580.1527 1374.0458) (2578.916 1377.9695)
      (2575.374 1381.4504) (2570.1069 1384.1985) (2563.9084 1386.0611) (2557.7252 1387.1603) (2552.3817 1387.8473)
      (2548.5649 1388.5802) (2546.5802 1389.9237) (2546.4122 1392.3053) (2547.6794 1395.9847) (2549.7557 1400.9466)
      (2551.9084 1406.8702) (2553.3893 1413.1603) (2553.4198 1413.9237) (2554.2443 1413.3435) (2564.4733 1407.4809)
      (2574.8397 1402.6565) (2585.1756 1398.916) (2595.2824 1396.3511) (2604.9924 1395.0076) (2603.0229 1405.3435)
      (2599.9542 1415.9542) (2595.8321 1426.6718) (2590.7328 1437.313) (2584.687 1447.7252) (2577.7557 1457.7252)
      (2570.0153 1467.1603) (2561.4809 1475.8473) (2552.229 1483.6183) (2542.3206 1490.3206) (2531.7863 1495.771)
      (2520.687 1499.8015) (2509.0992 1502.2595) (2497.0382 1502.9618) (2498.1832 1490.458) (2501.0534 1478.458)
      (2505.4351 1467.0076) (2511.1908 1456.1679) (2518.1374 1446.0153) (2526.0763 1436.5954) (2534.8702 1427.9695)
      (2538.4733 1425.0076) (2535.8015 1423.313) (2531.0992 1418.8702) (2527.0382 1414.0611) (2523.7863 1409.7863)
      (2521.2366 1406.8397) (2519.084 1405.8015) (2516.9313 1406.8397) (2514.3817 1409.7863) (2511.1298 1414.0611)
      (2507.0687 1418.8702) (2502.3664 1423.313) (2497.3588 1426.5038) (2492.5649 1427.8168) (2488.5496 1426.9313)
      (2485.771 1423.8931) (2484.5191 1419.084) (2484.7786 1413.1603) (2486.2595 1406.8702) (2488.4122 1400.9466)
      (2490.4885 1395.9847) (2491.7557 1392.3053) (2491.5878 1389.9237) (2489.6031 1388.5802) (2485.7863 1387.8473)
      (2480.4427 1387.1603) (2474.2595 1386.0611) (2468.0611 1384.1985) (2462.7939 1381.4504) (2459.2519 1377.9695)
    ))
    ; P2321 -- see feature_dimensions_mm.csv
    ("06_ORNAMENT" 1 (
      (2474.8092 5253.6947) (2493.1298 5233.084) (2511.4504 5253.6947) (2493.1298 5274.3053)
    ))
    ; P2322 -- see feature_dimensions_mm.csv
    ("06_ORNAMENT" 1 (
      (2474.8092 4942.2443) (2493.1298 4921.6336) (2511.4504 4942.2443) (2493.1298 4962.855)
    ))
    ; P2323 -- see feature_dimensions_mm.csv
    ("06_ORNAMENT" 1 (
      (2474.8092 4630.7939) (2493.1298 4610.1832) (2511.4504 4630.7939) (2493.1298 4651.4046)
    ))
    ; P2324 -- see feature_dimensions_mm.csv
    ("06_ORNAMENT" 1 (
      (2474.8092 4319.3435) (2493.1298 4298.7328) (2511.4504 4319.3435) (2493.1298 4339.9542)
    ))
    ; P2325 -- see feature_dimensions_mm.csv
    ("06_ORNAMENT" 1 (
      (2474.8092 4007.8931) (2493.1298 3987.2824) (2511.4504 4007.8931) (2493.1298 4028.5038)
    ))
    ; P2326 -- see feature_dimensions_mm.csv
    ("06_ORNAMENT" 1 (
      (2481.2214 5175.8321) (2482.1221 5171.2672) (2484.7023 5167.4046) (2488.5802 5164.8244) (2493.1298 5163.9237)
      (2497.6794 5164.8244) (2501.5573 5167.4046) (2504.1374 5171.2672) (2505.0382 5175.8321) (2504.1374 5180.3817)
      (2501.5573 5184.2443) (2497.6794 5186.8244) (2493.1298 5187.7405) (2488.5802 5186.8244) (2484.7023 5184.2443)
      (2482.1221 5180.3817)
    ))
    ; P2327 -- see feature_dimensions_mm.csv
    ("06_ORNAMENT" 1 (
      (2481.2214 4864.3817) (2482.1221 4859.8168) (2484.7023 4855.9542) (2488.5802 4853.374) (2493.1298 4852.4733)
      (2497.6794 4853.374) (2501.5573 4855.9542) (2504.1374 4859.8168) (2505.0382 4864.3817) (2504.1374 4868.9313)
      (2501.5573 4872.7939) (2497.6794 4875.374) (2493.1298 4876.2901) (2488.5802 4875.374) (2484.7023 4872.7939)
      (2482.1221 4868.9313)
    ))
    ; P2328 -- see feature_dimensions_mm.csv
    ("06_ORNAMENT" 1 (
      (2481.2214 4552.9313) (2482.1221 4548.3664) (2484.7023 4544.5038) (2488.5802 4541.9237) (2493.1298 4541.0229)
      (2497.6794 4541.9237) (2501.5573 4544.5038) (2504.1374 4548.3664) (2505.0382 4552.9313) (2504.1374 4557.4809)
      (2501.5573 4561.3435) (2497.6794 4563.9237) (2493.1298 4564.8397) (2488.5802 4563.9237) (2484.7023 4561.3435)
      (2482.1221 4557.4809)
    ))
    ; P2329 -- see feature_dimensions_mm.csv
    ("06_ORNAMENT" 1 (
      (2481.2214 4241.4809) (2482.1221 4236.916) (2484.7023 4233.0534) (2488.5802 4230.4733) (2493.1298 4229.5725)
      (2497.6794 4230.4733) (2501.5573 4233.0534) (2504.1374 4236.916) (2505.0382 4241.4809) (2504.1374 4246.0305)
      (2501.5573 4249.8931) (2497.6794 4252.4733) (2493.1298 4253.3893) (2488.5802 4252.4733) (2484.7023 4249.8931)
      (2482.1221 4246.0305)
    ))
    ; P2330 -- see feature_dimensions_mm.csv
    ("06_ORNAMENT" 1 (
      (2481.2214 3930.0305) (2482.1221 3925.4656) (2484.7023 3921.6031) (2488.5802 3919.0229) (2493.1298 3918.1221)
      (2497.6794 3919.0229) (2501.5573 3921.6031) (2504.1374 3925.4656) (2505.0382 3930.0305) (2504.1374 3934.5802)
      (2501.5573 3938.4427) (2497.6794 3941.0229) (2493.1298 3941.9389) (2488.5802 3941.0229) (2484.7023 3938.4427)
      (2482.1221 3934.5802)
    ))
    ; P2331 -- see feature_dimensions_mm.csv
    ("06_ORNAMENT" 1 (
      (2497.0382 1977.9542) (2509.542 1979.0992) (2521.542 1981.9695) (2532.9924 1986.3511) (2543.8321 1992.1069)
      (2553.9847 1999.0534) (2563.4046 2006.9924) (2572.0305 2015.7863) (2579.8015 2025.2214) (2586.6565 2035.1603)
      (2592.5191 2045.3893) (2597.3435 2055.7557) (2601.084 2066.0916) (2603.6489 2076.1985) (2604.9924 2085.9084)
      (2594.6565 2083.9389) (2584.0458 2080.8702) (2573.3282 2076.7481) (2562.687 2071.6489) (2552.2748 2065.6031)
      (2542.2748 2058.6718) (2532.8397 2050.9313) (2524.1527 2042.3969) (2516.3817 2033.145) (2509.6794 2023.2366)
      (2504.229 2012.7023) (2500.1985 2001.6031) (2497.7405 1990.0153)
    ))
    ; P2332 -- see feature_dimensions_mm.csv
    ("06_ORNAMENT" 1 (
      (2521.374 5331.5573) (2523.0687 5328.4122) (2527.6947 5325.8626) (2534.0 5324.1985) (2540.3206 5323.3282)
      (2545.0534 5322.7481) (2547.1603 5321.6794) (2546.4275 5319.4351) (2543.4962 5315.6794) (2539.6336 5310.6107)
      (2536.3511 5304.9771) (2534.8855 5299.8931) (2535.9084 5296.4733) (2539.3282 5295.4504) (2544.4122 5296.916)
      (2550.0458 5300.1985) (2555.1145 5304.0458) (2558.8702 5306.9771) (2561.1145 5307.7099) (2562.1832 5305.6183)
      (2562.7786 5300.8855) (2563.6336 5294.5649) (2565.2977 5288.2595) (2567.8473 5283.6336) (2570.9924 5281.9389)
      (2574.1374 5283.6336) (2576.687 5288.2595) (2578.3511 5294.5649) (2579.2061 5300.8855) (2579.8015 5305.6183)
      (2580.8702 5307.7099) (2583.1145 5306.9771) (2586.8702 5304.0458) (2591.9389 5300.1985) (2597.5725 5296.916)
      (2602.6565 5295.4504) (2606.0763 5296.4733) (2607.0992 5299.8931) (2605.6336 5304.9771) (2602.3511 5310.6107)
      (2598.4885 5315.6794) (2595.5573 5319.4351) (2594.8244 5321.6794) (2596.9313 5322.7481) (2601.6641 5323.3282)
      (2607.9847 5324.1985) (2614.2901 5325.8626) (2618.916 5328.4122) (2620.6107 5331.5573) (2618.916 5334.7023)
      (2614.2901 5337.2519) (2607.9847 5338.916) (2601.6641 5339.771) (2596.9313 5340.3664) (2594.8244 5341.4351)
      (2595.5573 5343.6794) (2598.4885 5347.4351) (2602.3511 5352.5038) (2605.6336 5358.1374) (2607.0992 5363.2214)
      (2606.0763 5366.6412) (2602.6565 5367.6641) (2597.5725 5366.1985) (2591.9389 5362.916) (2586.8702 5359.0534)
      (2583.1145 5356.1221) (2580.8702 5355.3893) (2579.8015 5357.4962) (2579.2061 5362.229) (2578.3511 5368.5344)
      (2576.687 5374.8397) (2574.1374 5379.4809) (2570.9924 5381.1756) (2567.8473 5379.4809) (2565.2977 5374.8397)
      (2563.6336 5368.5344) (2562.7786 5362.229) (2562.1832 5357.4962) (2561.1145 5355.3893) (2558.8702 5356.1221)
      (2555.1145 5359.0534) (2550.0458 5362.916) (2544.4122 5366.1985) (2539.3282 5367.6641) (2535.9084 5366.6412)
      (2534.8855 5363.2214) (2536.3511 5358.1374) (2539.6336 5352.5038) (2543.4962 5347.4351) (2546.4275 5343.6794)
      (2547.1603 5341.4351) (2545.0534 5340.3664) (2540.3206 5339.771) (2534.0 5338.916) (2527.6947 5337.2519)
      (2523.0687 5334.7023)
    ))
    ; P2333 -- see feature_dimensions_mm.csv
    ("06_ORNAMENT" 1 (
      (2521.374 5020.1069) (2523.0687 5016.9618) (2527.6947 5014.4122) (2534.0 5012.7481) (2540.3206 5011.8779)
      (2545.0534 5011.2977) (2547.1603 5010.229) (2546.4275 5007.9847) (2543.4962 5004.229) (2539.6336 4999.1603)
      (2536.3511 4993.5267) (2534.8855 4988.4427) (2535.9084 4985.0229) (2539.3282 4984.0) (2544.4122 4985.4656)
      (2550.0458 4988.7481) (2555.1145 4992.5954) (2558.8702 4995.5267) (2561.1145 4996.2595) (2562.1832 4994.1679)
      (2562.7786 4989.4351) (2563.6336 4983.1145) (2565.2977 4976.8092) (2567.8473 4972.1832) (2570.9924 4970.4885)
      (2574.1374 4972.1832) (2576.687 4976.8092) (2578.3511 4983.1145) (2579.2061 4989.4351) (2579.8015 4994.1679)
      (2580.8702 4996.2595) (2583.1145 4995.5267) (2586.8702 4992.5954) (2591.9389 4988.7481) (2597.5725 4985.4656)
      (2602.6565 4984.0) (2606.0763 4985.0229) (2607.0992 4988.4427) (2605.6336 4993.5267) (2602.3511 4999.1603)
      (2598.4885 5004.229) (2595.5573 5007.9847) (2594.8244 5010.229) (2596.9313 5011.2977) (2601.6641 5011.8779)
      (2607.9847 5012.7481) (2614.2901 5014.4122) (2618.916 5016.9618) (2620.6107 5020.1069) (2618.916 5023.2519)
      (2614.2901 5025.8015) (2607.9847 5027.4656) (2601.6641 5028.3206) (2596.9313 5028.916) (2594.8244 5029.9847)
      (2595.5573 5032.229) (2598.4885 5035.9847) (2602.3511 5041.0534) (2605.6336 5046.687) (2607.0992 5051.771)
      (2606.0763 5055.1908) (2602.6565 5056.2137) (2597.5725 5054.7481) (2591.9389 5051.4656) (2586.8702 5047.6031)
      (2583.1145 5044.6718) (2580.8702 5043.9389) (2579.8015 5046.0458) (2579.2061 5050.7786) (2578.3511 5057.084)
      (2576.687 5063.3893) (2574.1374 5068.0305) (2570.9924 5069.7252) (2567.8473 5068.0305) (2565.2977 5063.3893)
      (2563.6336 5057.084) (2562.7786 5050.7786) (2562.1832 5046.0458) (2561.1145 5043.9389) (2558.8702 5044.6718)
      (2555.1145 5047.6031) (2550.0458 5051.4656) (2544.4122 5054.7481) (2539.3282 5056.2137) (2535.9084 5055.1908)
      (2534.8855 5051.771) (2536.3511 5046.687) (2539.6336 5041.0534) (2543.4962 5035.9847) (2546.4275 5032.229)
      (2547.1603 5029.9847) (2545.0534 5028.916) (2540.3206 5028.3206) (2534.0 5027.4656) (2527.6947 5025.8015)
      (2523.0687 5023.2519)
    ))
    ; P2334 -- see feature_dimensions_mm.csv
    ("06_ORNAMENT" 1 (
      (2521.374 4708.6565) (2523.0687 4705.5115) (2527.6947 4702.9618) (2534.0 4701.2977) (2540.3206 4700.4275)
      (2545.0534 4699.8473) (2547.1603 4698.7786) (2546.4275 4696.5344) (2543.4962 4692.7786) (2539.6336 4687.7099)
      (2536.3511 4682.0763) (2534.8855 4676.9924) (2535.9084 4673.5725) (2539.3282 4672.5496) (2544.4122 4674.0153)
      (2550.0458 4677.2977) (2555.1145 4681.145) (2558.8702 4684.0763) (2561.1145 4684.8092) (2562.1832 4682.7176)
      (2562.7786 4677.9847) (2563.6336 4671.6641) (2565.2977 4665.3588) (2567.8473 4660.7328) (2570.9924 4659.0382)
      (2574.1374 4660.7328) (2576.687 4665.3588) (2578.3511 4671.6641) (2579.2061 4677.9847) (2579.8015 4682.7176)
      (2580.8702 4684.8092) (2583.1145 4684.0763) (2586.8702 4681.145) (2591.9389 4677.2977) (2597.5725 4674.0153)
      (2602.6565 4672.5496) (2606.0763 4673.5725) (2607.0992 4676.9924) (2605.6336 4682.0763) (2602.3511 4687.7099)
      (2598.4885 4692.7786) (2595.5573 4696.5344) (2594.8244 4698.7786) (2596.9313 4699.8473) (2601.6641 4700.4275)
      (2607.9847 4701.2977) (2614.2901 4702.9618) (2618.916 4705.5115) (2620.6107 4708.6565) (2618.916 4711.8015)
      (2614.2901 4714.3511) (2607.9847 4716.0153) (2601.6641 4716.8702) (2596.9313 4717.4656) (2594.8244 4718.5344)
      (2595.5573 4720.7786) (2598.4885 4724.5344) (2602.3511 4729.6031) (2605.6336 4735.2366) (2607.0992 4740.3206)
      (2606.0763 4743.7405) (2602.6565 4744.7634) (2597.5725 4743.2977) (2591.9389 4740.0153) (2586.8702 4736.1527)
      (2583.1145 4733.2214) (2580.8702 4732.4885) (2579.8015 4734.5954) (2579.2061 4739.3282) (2578.3511 4745.6336)
      (2576.687 4751.9389) (2574.1374 4756.5802) (2570.9924 4758.2748) (2567.8473 4756.5802) (2565.2977 4751.9389)
      (2563.6336 4745.6336) (2562.7786 4739.3282) (2562.1832 4734.5954) (2561.1145 4732.4885) (2558.8702 4733.2214)
      (2555.1145 4736.1527) (2550.0458 4740.0153) (2544.4122 4743.2977) (2539.3282 4744.7634) (2535.9084 4743.7405)
      (2534.8855 4740.3206) (2536.3511 4735.2366) (2539.6336 4729.6031) (2543.4962 4724.5344) (2546.4275 4720.7786)
      (2547.1603 4718.5344) (2545.0534 4717.4656) (2540.3206 4716.8702) (2534.0 4716.0153) (2527.6947 4714.3511)
      (2523.0687 4711.8015)
    ))
    ; P2335 -- see feature_dimensions_mm.csv
    ("06_ORNAMENT" 1 (
      (2521.374 4397.2061) (2523.0687 4394.0611) (2527.6947 4391.5115) (2534.0 4389.8473) (2540.3206 4388.9771)
      (2545.0534 4388.3969) (2547.1603 4387.3282) (2546.4275 4385.084) (2543.4962 4381.3282) (2539.6336 4376.2595)
      (2536.3511 4370.626) (2534.8855 4365.542) (2535.9084 4362.1221) (2539.3282 4361.0992) (2544.4122 4362.5649)
      (2550.0458 4365.8473) (2555.1145 4369.6947) (2558.8702 4372.626) (2561.1145 4373.3588) (2562.1832 4371.2672)
      (2562.7786 4366.5344) (2563.6336 4360.2137) (2565.2977 4353.9084) (2567.8473 4349.2824) (2570.9924 4347.5878)
      (2574.1374 4349.2824) (2576.687 4353.9084) (2578.3511 4360.2137) (2579.2061 4366.5344) (2579.8015 4371.2672)
      (2580.8702 4373.3588) (2583.1145 4372.626) (2586.8702 4369.6947) (2591.9389 4365.8473) (2597.5725 4362.5649)
      (2602.6565 4361.0992) (2606.0763 4362.1221) (2607.0992 4365.542) (2605.6336 4370.626) (2602.3511 4376.2595)
      (2598.4885 4381.3282) (2595.5573 4385.084) (2594.8244 4387.3282) (2596.9313 4388.3969) (2601.6641 4388.9771)
      (2607.9847 4389.8473) (2614.2901 4391.5115) (2618.916 4394.0611) (2620.6107 4397.2061) (2618.916 4400.3511)
      (2614.2901 4402.9008) (2607.9847 4404.5649) (2601.6641 4405.4198) (2596.9313 4406.0153) (2594.8244 4407.084)
      (2595.5573 4409.3282) (2597.8168 4412.2137) (2544.1679 4412.2137) (2546.4275 4409.3282) (2547.1603 4407.084)
      (2545.0534 4406.0153) (2540.3206 4405.4198) (2534.0 4404.5649) (2527.6947 4402.9008) (2523.0687 4400.3511)
    ))
    ; P2336 -- see feature_dimensions_mm.csv
    ("06_ORNAMENT" 1 (
      (2521.374 4085.7557) (2523.0687 4082.6107) (2527.6947 4080.0611) (2534.0 4078.3969) (2540.3206 4077.5267)
      (2545.0534 4076.9466) (2547.1603 4075.8779) (2546.4275 4073.6336) (2543.4962 4069.8779) (2539.6336 4064.8092)
      (2536.3511 4059.1756) (2534.8855 4054.0916) (2535.9084 4050.6718) (2539.3282 4049.6489) (2544.4122 4051.1145)
      (2550.0458 4054.3969) (2555.1145 4058.2595) (2558.8702 4061.1756) (2561.1145 4061.9084) (2562.1832 4059.8168)
      (2562.7786 4055.084) (2563.6336 4048.7634) (2565.2977 4042.458) (2567.8473 4037.8321) (2570.9924 4036.1374)
      (2574.1374 4037.8321) (2576.687 4042.458) (2578.3511 4048.7634) (2579.2061 4055.084) (2579.8015 4059.8168)
      (2580.8702 4061.9084) (2583.1145 4061.1756) (2586.8702 4058.2595) (2591.9389 4054.3969) (2597.5725 4051.1145)
      (2602.6565 4049.6489) (2606.0763 4050.6718) (2607.0992 4054.0916) (2605.6336 4059.1756) (2602.3511 4064.8092)
      (2598.4885 4069.8779) (2595.5573 4073.6336) (2594.8244 4075.8779) (2596.9313 4076.9466) (2601.6641 4077.5267)
      (2607.9847 4078.3969) (2614.2901 4080.0611) (2618.916 4082.6107) (2620.6107 4085.7557) (2618.916 4088.9008)
      (2614.2901 4091.4504) (2607.9847 4093.1145) (2601.6641 4093.9695) (2596.9313 4094.5649) (2594.8244 4095.6336)
      (2595.5573 4097.8779) (2598.4885 4101.6336) (2602.3511 4106.7023) (2605.6336 4112.3359) (2607.0992 4117.4198)
      (2606.0763 4120.8397) (2602.6565 4121.8626) (2597.5725 4120.3969) (2591.9389 4117.1145) (2586.8702 4113.2519)
      (2583.1145 4110.3206) (2580.8702 4109.5878) (2579.8015 4111.6947) (2579.2061 4116.4275) (2578.3511 4122.7328)
      (2576.687 4129.0382) (2574.1374 4133.6794) (2570.9924 4135.374) (2567.8473 4133.6794) (2565.2977 4129.0382)
      (2563.6336 4122.7328) (2562.7786 4116.4275) (2562.1832 4111.6947) (2561.1145 4109.5878) (2558.8702 4110.3206)
      (2555.1145 4113.2519) (2550.0458 4117.1145) (2544.4122 4120.3969) (2539.3282 4121.8626) (2535.9084 4120.8397)
      (2534.8855 4117.4198) (2536.3511 4112.3359) (2539.6336 4106.7023) (2543.4962 4101.6336) (2546.4275 4097.8779)
      (2547.1603 4095.6336) (2545.0534 4094.5649) (2540.3206 4093.9695) (2534.0 4093.1145) (2527.6947 4091.4504)
      (2523.0687 4088.9008)
    ))
    ; P2337 -- see feature_dimensions_mm.csv
    ("06_ORNAMENT" 1 (
      (2549.6183 3007.6336) (2580.1527 2977.0992) (2610.687 3007.6336) (2580.1527 3038.1679)
    ))
    ; P2338 -- see feature_dimensions_mm.csv
    ("06_ORNAMENT" 1 (
      (2549.6183 2916.0305) (2580.1527 2885.4962) (2610.687 2916.0305) (2580.1527 2946.5649)
    ))
    ; P2339 -- see feature_dimensions_mm.csv
    ("06_ORNAMENT" 1 (
      (2552.6718 5409.4198) (2570.9924 5388.8092) (2589.313 5409.4198) (2570.9924 5430.0305)
    ))
    ; P2340 -- see feature_dimensions_mm.csv
    ("06_ORNAMENT" 1 (
      (2552.6718 5097.9695) (2570.9924 5077.3588) (2589.313 5097.9695) (2570.9924 5118.5802)
    ))
    ; P2341 -- see feature_dimensions_mm.csv
    ("06_ORNAMENT" 1 (
      (2552.6718 4786.5191) (2570.9924 4765.9084) (2589.313 4786.5191) (2570.9924 4807.1298)
    ))
    ; P2342 -- see feature_dimensions_mm.csv
    ("06_ORNAMENT" 1 (
      (2552.6718 4163.6183) (2570.9924 4143.0076) (2589.313 4163.6183) (2570.9924 4184.229)
    ))
    ; P2343 -- see feature_dimensions_mm.csv
    ("06_ORNAMENT" 1 (
      (2559.084 5331.5573) (2559.9847 5326.9924) (2562.5649 5323.1298) (2566.4427 5320.5496) (2570.9924 5319.6489)
      (2575.542 5320.5496) (2579.4198 5323.1298) (2582.0 5326.9924) (2582.9008 5331.5573) (2582.0 5336.1069)
      (2579.4198 5339.9695) (2575.542 5342.5496) (2570.9924 5343.4656) (2566.4427 5342.5496) (2562.5649 5339.9695)
      (2559.9847 5336.1069)
    ))
    ; P2344 -- see feature_dimensions_mm.csv
    ("06_ORNAMENT" 1 (
      (2559.084 5020.1069) (2559.9847 5015.542) (2562.5649 5011.6794) (2566.4427 5009.0992) (2570.9924 5008.1985)
      (2575.542 5009.0992) (2579.4198 5011.6794) (2582.0 5015.542) (2582.9008 5020.1069) (2582.0 5024.6565)
      (2579.4198 5028.5191) (2575.542 5031.0992) (2570.9924 5032.0153) (2566.4427 5031.0992) (2562.5649 5028.5191)
      (2559.9847 5024.6565)
    ))
    ; P2345 -- see feature_dimensions_mm.csv
    ("06_ORNAMENT" 1 (
      (2559.084 4708.6565) (2559.9847 4704.0916) (2562.5649 4700.229) (2566.4427 4697.6489) (2570.9924 4696.7481)
      (2575.542 4697.6489) (2579.4198 4700.229) (2582.0 4704.0916) (2582.9008 4708.6565) (2582.0 4713.2061)
      (2579.4198 4717.0687) (2575.542 4719.6489) (2570.9924 4720.5649) (2566.4427 4719.6489) (2562.5649 4717.0687)
      (2559.9847 4713.2061)
    ))
    ; P2346 -- see feature_dimensions_mm.csv
    ("06_ORNAMENT" 1 (
      (2559.084 4397.2061) (2559.9847 4392.6412) (2562.5649 4388.7786) (2566.4427 4386.1985) (2570.9924 4385.2977)
      (2575.542 4386.1985) (2579.4198 4388.7786) (2582.0 4392.6412) (2582.9008 4397.2061) (2582.0 4401.7557)
      (2579.4198 4405.6183) (2575.542 4408.1985) (2570.9924 4409.1145) (2566.4427 4408.1985) (2562.5649 4405.6183)
      (2559.9847 4401.7557)
    ))
    ; P2347 -- see feature_dimensions_mm.csv
    ("06_ORNAMENT" 1 (
      (2559.084 4085.7557) (2559.9847 4081.1908) (2562.5649 4077.3282) (2566.4427 4074.7481) (2570.9924 4073.8473)
      (2575.542 4074.7481) (2579.4198 4077.3282) (2582.0 4081.1908) (2582.9008 4085.7557) (2582.0 4090.3053)
      (2579.4198 4094.1679) (2575.542 4096.7481) (2570.9924 4097.6641) (2566.4427 4096.7481) (2562.5649 4094.1679)
      (2559.9847 4090.3053)
    ))
    ; P2348 -- see feature_dimensions_mm.csv
    ("06_ORNAMENT" 1 (
      (2583.9695 1827.3893) (2595.374 1822.1374) (2607.1908 1818.6107) (2619.313 1816.687) (2631.5725 1816.2595)
      (2643.8321 1817.1908) (2655.9695 1819.3588) (2667.8321 1822.6565) (2679.2824 1826.9466) (2690.1679 1832.1221)
      (2700.3817 1838.0458) (2709.7405 1844.6107) (2717.3282 1851.0076) (2716.6107 1871.5725) (2710.7634 1873.0076)
      (2699.4351 1874.7939) (2687.6641 1875.6947) (2675.6336 1875.6794) (2663.4962 1874.6718) (2651.4656 1872.6718)
      (2639.6794 1869.6336) (2628.3206 1865.5115) (2617.5573 1860.2748) (2607.5725 1853.8779) (2598.5344 1846.2901)
      (2590.6107 1837.4809)
    ))
    ; P2349 -- see feature_dimensions_mm.csv
    ("06_ORNAMENT" 1 (
      (2583.9695 1653.5267) (2591.2214 1643.2824) (2599.6947 1634.3053) (2609.2214 1626.5954) (2619.6183 1620.0916)
      (2630.7176 1614.7634) (2642.3053 1610.5802) (2654.229 1607.4962) (2666.2901 1605.4962) (2678.3053 1604.5191)
      (2690.1069 1604.5649) (2701.5115 1605.5573) (2712.3206 1607.4962) (2717.5573 1608.9618) (2717.5573 1628.7023)
      (2716.5954 1629.6336) (2707.6641 1636.855) (2697.9237 1643.5267) (2687.4962 1649.5115) (2676.4885 1654.7176)
      (2665.0687 1659.0076) (2653.3435 1662.2595) (2641.4351 1664.3664) (2629.4962 1665.2214) (2617.6489 1664.6718)
      (2606.0305 1662.626) (2594.7634 1658.9466)
    ))
    ; P2350 -- see feature_dimensions_mm.csv
    ("06_ORNAMENT" 1 (
      (2599.2366 5175.8321) (2600.9313 5172.687) (2605.5573 5170.1374) (2611.8626 5168.4733) (2618.1832 5167.6031)
      (2622.916 5167.0229) (2625.0229 5165.9542) (2624.2901 5163.7099) (2621.3588 5159.9542) (2617.4962 5154.8855)
      (2614.2137 5149.2519) (2612.7481 5144.1679) (2613.771 5140.7481) (2617.1908 5139.7252) (2622.2748 5141.1908)
      (2627.9084 5144.4733) (2632.9771 5148.3206) (2636.7328 5151.2519) (2638.9771 5151.9847) (2640.0458 5149.8931)
      (2640.6412 5145.1603) (2641.4962 5138.8397) (2643.1603 5132.5344) (2645.7099 5127.9084) (2648.855 5126.2137)
      (2652.0 5127.9084) (2654.5496 5132.5344) (2656.2137 5138.8397) (2657.0687 5145.1603) (2657.6641 5149.8931)
      (2658.7328 5151.9847) (2660.9771 5151.2519) (2664.7328 5148.3206) (2669.8015 5144.4733) (2675.4351 5141.1908)
      (2680.5191 5139.7252) (2683.9389 5140.7481) (2684.9618 5144.1679) (2683.4962 5149.2519) (2680.2137 5154.8855)
      (2676.3511 5159.9542) (2673.4198 5163.7099) (2672.687 5165.9542) (2674.7939 5167.0229) (2679.5267 5167.6031)
      (2685.8473 5168.4733) (2692.1527 5170.1374) (2696.7786 5172.687) (2698.4733 5175.8321) (2696.7786 5178.9771)
      (2692.1527 5181.5267) (2685.8473 5183.1908) (2679.5267 5184.0458) (2674.7939 5184.6412) (2672.687 5185.7099)
      (2673.4198 5187.9542) (2676.3511 5191.7099) (2680.2137 5196.7786) (2683.4962 5202.4122) (2684.9618 5207.4962)
      (2683.9389 5210.916) (2680.5191 5211.9389) (2675.4351 5210.4733) (2669.8015 5207.1908) (2664.7328 5203.3282)
      (2660.9771 5200.3969) (2658.7328 5199.6641) (2657.6641 5201.771) (2657.0687 5206.5038) (2656.2137 5212.8092)
      (2654.5496 5219.1145) (2652.0 5223.7557) (2648.855 5225.4504) (2645.7099 5223.7557) (2643.1603 5219.1145)
      (2641.4962 5212.8092) (2640.6412 5206.5038) (2640.0458 5201.771) (2638.9771 5199.6641) (2636.7328 5200.3969)
      (2632.9771 5203.3282) (2627.9084 5207.1908) (2622.2748 5210.4733) (2617.1908 5211.9389) (2613.771 5210.916)
      (2612.7481 5207.4962) (2614.2137 5202.4122) (2617.4962 5196.7786) (2621.3588 5191.7099) (2624.2901 5187.9542)
      (2625.0229 5185.7099) (2622.916 5184.6412) (2618.1832 5184.0458) (2611.8626 5183.1908) (2605.5573 5181.5267)
      (2600.9313 5178.9771)
    ))
    ; P2351 -- see feature_dimensions_mm.csv
    ("06_ORNAMENT" 1 (
      (2599.2366 4864.3817) (2600.9313 4861.2366) (2605.5573 4858.687) (2611.8626 4857.0229) (2618.1832 4856.1527)
      (2622.916 4855.5725) (2625.0229 4854.5038) (2624.2901 4852.2595) (2621.3588 4848.5038) (2617.4962 4843.4351)
      (2614.2137 4837.8015) (2612.7481 4832.7176) (2613.771 4829.2977) (2617.1908 4828.2748) (2622.2748 4829.7405)
      (2627.9084 4833.0229) (2632.9771 4836.8702) (2636.7328 4839.8015) (2638.9771 4840.5344) (2640.0458 4838.4427)
      (2640.6412 4833.7099) (2641.4962 4827.3893) (2643.1603 4821.084) (2645.7099 4816.458) (2648.855 4814.7634)
      (2652.0 4816.458) (2654.5496 4821.084) (2656.2137 4827.3893) (2657.0687 4833.7099) (2657.6641 4838.4427)
      (2658.7328 4840.5344) (2660.9771 4839.8015) (2664.7328 4836.8702) (2669.8015 4833.0229) (2675.4351 4829.7405)
      (2680.5191 4828.2748) (2683.9389 4829.2977) (2684.9618 4832.7176) (2683.4962 4837.8015) (2680.2137 4843.4351)
      (2676.3511 4848.5038) (2673.4198 4852.2595) (2672.687 4854.5038) (2674.7939 4855.5725) (2679.5267 4856.1527)
      (2685.8473 4857.0229) (2692.1527 4858.687) (2696.7786 4861.2366) (2698.4733 4864.3817) (2696.7786 4867.5267)
      (2692.1527 4870.0763) (2685.8473 4871.7405) (2679.5267 4872.5954) (2674.7939 4873.1908) (2672.687 4874.2595)
      (2673.4198 4876.5038) (2676.3511 4880.2595) (2680.2137 4885.3282) (2683.4962 4890.9618) (2684.9618 4896.0458)
      (2683.9389 4899.4656) (2680.5191 4900.4885) (2675.4351 4899.0229) (2669.8015 4895.7405) (2664.7328 4891.8779)
      (2660.9771 4888.9466) (2658.7328 4888.2137) (2657.6641 4890.3206) (2657.0687 4895.0534) (2656.2137 4901.3588)
      (2654.5496 4907.6641) (2652.0 4912.3053) (2648.855 4914.0) (2645.7099 4912.3053) (2643.1603 4907.6641)
      (2641.4962 4901.3588) (2640.6412 4895.0534) (2640.0458 4890.3206) (2638.9771 4888.2137) (2636.7328 4888.9466)
      (2632.9771 4891.8779) (2627.9084 4895.7405) (2622.2748 4899.0229) (2617.1908 4900.4885) (2613.771 4899.4656)
      (2612.7481 4896.0458) (2614.2137 4890.9618) (2617.4962 4885.3282) (2621.3588 4880.2595) (2624.2901 4876.5038)
      (2625.0229 4874.2595) (2622.916 4873.1908) (2618.1832 4872.5954) (2611.8626 4871.7405) (2605.5573 4870.0763)
      (2600.9313 4867.5267)
    ))
    ; P2352 -- see feature_dimensions_mm.csv
    ("06_ORNAMENT" 1 (
      (2599.2366 4552.9313) (2600.9313 4549.7863) (2605.5573 4547.2366) (2611.8626 4545.5725) (2618.1832 4544.7023)
      (2622.916 4544.1221) (2625.0229 4543.0534) (2624.2901 4540.8092) (2621.3588 4537.0534) (2617.4962 4531.9847)
      (2614.2137 4526.3511) (2612.7481 4521.2672) (2613.771 4517.8473) (2617.1908 4516.8244) (2622.2748 4518.2901)
      (2627.9084 4521.5725) (2632.9771 4525.4198) (2636.7328 4528.3511) (2638.9771 4529.084) (2640.0458 4526.9924)
      (2640.6412 4522.2595) (2641.4962 4515.9389) (2643.1603 4509.6336) (2645.7099 4505.0076) (2648.855 4503.313)
      (2652.0 4505.0076) (2654.5496 4509.6336) (2656.2137 4515.9389) (2657.0687 4522.2595) (2657.6641 4526.9924)
      (2658.7328 4529.084) (2660.9771 4528.3511) (2664.7328 4525.4198) (2669.8015 4521.5725) (2675.4351 4518.2901)
      (2680.5191 4516.8244) (2683.9389 4517.8473) (2684.9618 4521.2672) (2683.4962 4526.3511) (2680.2137 4531.9847)
      (2676.3511 4537.0534) (2673.4198 4540.8092) (2672.687 4543.0534) (2674.7939 4544.1221) (2679.5267 4544.7023)
      (2685.8473 4545.5725) (2692.1527 4547.2366) (2696.7786 4549.7863) (2698.4733 4552.9313) (2696.7786 4556.0763)
      (2692.1527 4558.626) (2685.8473 4560.2901) (2679.5267 4561.145) (2674.7939 4561.7405) (2672.687 4562.8092)
      (2673.4198 4565.0534) (2676.3511 4568.8092) (2680.2137 4573.8779) (2683.4962 4579.5115) (2684.9618 4584.5954)
      (2683.9389 4588.0153) (2680.5191 4589.0382) (2675.4351 4587.5725) (2669.8015 4584.2901) (2664.7328 4580.4275)
      (2660.9771 4577.4962) (2658.7328 4576.7634) (2657.6641 4578.8702) (2657.0687 4583.6031) (2656.2137 4589.9084)
      (2654.5496 4596.2137) (2652.0 4600.855) (2648.855 4602.5496) (2645.7099 4600.855) (2643.1603 4596.2137)
      (2641.4962 4589.9084) (2640.6412 4583.6031) (2640.0458 4578.8702) (2638.9771 4576.7634) (2636.7328 4577.4962)
      (2632.9771 4580.4275) (2627.9084 4584.2901) (2622.2748 4587.5725) (2617.1908 4589.0382) (2613.771 4588.0153)
      (2612.7481 4584.5954) (2614.2137 4579.5115) (2617.4962 4573.8779) (2621.3588 4568.8092) (2624.2901 4565.0534)
      (2625.0229 4562.8092) (2622.916 4561.7405) (2618.1832 4561.145) (2611.8626 4560.2901) (2605.5573 4558.626)
      (2600.9313 4556.0763)
    ))
    ; P2353 -- see feature_dimensions_mm.csv
    ("06_ORNAMENT" 1 (
      (2599.2366 4241.4809) (2600.9313 4238.3359) (2605.5573 4235.7863) (2611.8626 4234.1221) (2618.1832 4233.2519)
      (2622.916 4232.6718) (2625.0229 4231.6031) (2624.2901 4229.3588) (2621.3588 4225.6031) (2617.4962 4220.5344)
      (2614.2137 4214.9008) (2612.7481 4209.8168) (2613.771 4206.3969) (2617.1908 4205.374) (2622.2748 4206.8397)
      (2627.9084 4210.1221) (2632.9771 4213.9695) (2636.7328 4216.9008) (2638.9771 4217.6336) (2640.0458 4215.542)
      (2640.6412 4210.8092) (2641.4962 4204.4885) (2643.1603 4198.1832) (2645.7099 4193.5573) (2648.855 4191.8626)
      (2652.0 4193.5573) (2654.5496 4198.1832) (2656.2137 4204.4885) (2657.0687 4210.8092) (2657.6641 4215.542)
      (2658.7328 4217.6336) (2660.9771 4216.9008) (2664.7328 4213.9695) (2669.8015 4210.1221) (2675.4351 4206.8397)
      (2680.5191 4205.374) (2683.9389 4206.3969) (2684.9618 4209.8168) (2683.4962 4214.9008) (2680.2137 4220.5344)
      (2676.3511 4225.6031) (2673.4198 4229.3588) (2672.687 4231.6031) (2674.7939 4232.6718) (2679.5267 4233.2519)
      (2685.8473 4234.1221) (2692.1527 4235.7863) (2696.7786 4238.3359) (2698.4733 4241.4809) (2696.7786 4244.626)
      (2692.1527 4247.1756) (2685.8473 4248.8397) (2679.5267 4249.6947) (2674.7939 4250.2901) (2672.687 4251.3588)
      (2673.4198 4253.6031) (2676.3511 4257.3588) (2680.2137 4262.4275) (2683.4962 4268.0611) (2684.9618 4273.145)
      (2683.9389 4276.5649) (2680.5191 4277.5878) (2675.4351 4276.1221) (2669.8015 4272.8397) (2664.7328 4268.9771)
      (2660.9771 4266.0458) (2658.7328 4265.313) (2657.6641 4267.4198) (2657.0687 4272.1527) (2656.2137 4278.458)
      (2654.5496 4284.7634) (2652.0 4289.4046) (2648.855 4291.0992) (2645.7099 4289.4046) (2643.1603 4284.7634)
      (2641.4962 4278.458) (2640.6412 4272.1527) (2640.0458 4267.4198) (2638.9771 4265.313) (2636.7328 4266.0458)
      (2632.9771 4268.9771) (2627.9084 4272.8397) (2622.2748 4276.1221) (2617.1908 4277.5878) (2613.771 4276.5649)
      (2612.7481 4273.145) (2614.2137 4268.0611) (2617.4962 4262.4275) (2621.3588 4257.3588) (2624.2901 4253.6031)
      (2625.0229 4251.3588) (2622.916 4250.2901) (2618.1832 4249.6947) (2611.8626 4248.8397) (2605.5573 4247.1756)
      (2600.9313 4244.626)
    ))
    ; P2354 -- see feature_dimensions_mm.csv
    ("06_ORNAMENT" 1 (
      (2599.2366 3930.0305) (2600.9313 3926.8855) (2605.5573 3924.3359) (2611.8626 3922.6718) (2618.1832 3921.8015)
      (2622.916 3921.2214) (2625.0229 3920.1527) (2624.2901 3917.9084) (2621.3588 3914.1527) (2617.4962 3909.084)
      (2614.2137 3903.4504) (2612.7481 3898.3664) (2613.771 3894.9466) (2617.1908 3893.9237) (2622.2748 3895.3893)
      (2627.9084 3898.6718) (2632.9771 3902.5191) (2636.7328 3905.4504) (2638.9771 3906.1832) (2640.0458 3904.0916)
      (2640.6412 3899.3588) (2641.4962 3893.0382) (2643.1603 3886.7328) (2645.7099 3882.1069) (2648.855 3880.4122)
      (2652.0 3882.1069) (2654.5496 3886.7328) (2656.2137 3893.0382) (2657.0687 3899.3588) (2657.6641 3904.0916)
      (2658.7328 3906.1832) (2660.9771 3905.4504) (2664.7328 3902.5191) (2669.8015 3898.6718) (2675.4351 3895.3893)
      (2680.5191 3893.9237) (2683.9389 3894.9466) (2684.9618 3898.3664) (2683.4962 3903.4504) (2680.2137 3909.084)
      (2676.3511 3914.1527) (2673.4198 3917.9084) (2672.687 3920.1527) (2674.7939 3921.2214) (2679.5267 3921.8015)
      (2685.8473 3922.6718) (2692.1527 3924.3359) (2696.7786 3926.8855) (2698.4733 3930.0305) (2696.7786 3933.1756)
      (2692.1527 3935.7252) (2685.8473 3937.3893) (2679.5267 3938.2443) (2674.7939 3938.8397) (2672.687 3939.9084)
      (2673.4198 3942.1527) (2676.3511 3945.9084) (2680.2137 3950.9771) (2683.4962 3956.6107) (2684.9618 3961.6947)
      (2683.9389 3965.1145) (2680.5191 3966.1374) (2675.4351 3964.6718) (2669.8015 3961.3893) (2664.7328 3957.5267)
      (2660.9771 3954.5954) (2658.7328 3953.8626) (2657.6641 3955.9695) (2657.0687 3960.7023) (2656.2137 3967.0076)
      (2654.5496 3973.313) (2652.0 3977.9542) (2648.855 3979.6489) (2645.7099 3977.9542) (2643.1603 3973.313)
      (2641.4962 3967.0076) (2640.6412 3960.7023) (2640.0458 3955.9695) (2638.9771 3953.8626) (2636.7328 3954.5954)
      (2632.9771 3957.5267) (2627.9084 3961.3893) (2622.2748 3964.6718) (2617.1908 3966.1374) (2613.771 3965.1145)
      (2612.7481 3961.6947) (2614.2137 3956.6107) (2617.4962 3950.9771) (2621.3588 3945.9084) (2624.2901 3942.1527)
      (2625.0229 3939.9084) (2622.916 3938.8397) (2618.1832 3938.2443) (2611.8626 3937.3893) (2605.5573 3935.7252)
      (2600.9313 3933.1756)
    ))
    ; P2355 -- see feature_dimensions_mm.csv
    ("06_ORNAMENT" 1 (
      (2630.5344 5253.6947) (2648.855 5233.084) (2667.1756 5253.6947) (2648.855 5274.3053)
    ))
    ; P2356 -- see feature_dimensions_mm.csv
    ("06_ORNAMENT" 1 (
      (2630.5344 4942.2443) (2648.855 4921.6336) (2667.1756 4942.2443) (2648.855 4962.855)
    ))
    ; P2357 -- see feature_dimensions_mm.csv
    ("06_ORNAMENT" 1 (
      (2630.5344 4630.7939) (2648.855 4610.1832) (2667.1756 4630.7939) (2648.855 4651.4046)
    ))
    ; P2358 -- see feature_dimensions_mm.csv
    ("06_ORNAMENT" 1 (
      (2630.5344 4319.3435) (2648.855 4298.7328) (2667.1756 4319.3435) (2648.855 4339.9542)
    ))
    ; P2359 -- see feature_dimensions_mm.csv
    ("06_ORNAMENT" 1 (
      (2630.5344 4007.8931) (2648.855 3987.2824) (2667.1756 4007.8931) (2648.855 4028.5038)
    ))
    ; P2360 -- see feature_dimensions_mm.csv
    ("06_ORNAMENT" 1 (
      (2636.9466 5175.8321) (2637.8473 5171.2672) (2640.4275 5167.4046) (2644.3053 5164.8244) (2648.855 5163.9237)
      (2653.4046 5164.8244) (2657.2824 5167.4046) (2659.8626 5171.2672) (2660.7634 5175.8321) (2659.8626 5180.3817)
      (2657.2824 5184.2443) (2653.4046 5186.8244) (2648.855 5187.7405) (2644.3053 5186.8244) (2640.4275 5184.2443)
      (2637.8473 5180.3817)
    ))
    ; P2361 -- see feature_dimensions_mm.csv
    ("06_ORNAMENT" 1 (
      (2636.9466 4864.3817) (2637.8473 4859.8168) (2640.4275 4855.9542) (2644.3053 4853.374) (2648.855 4852.4733)
      (2653.4046 4853.374) (2657.2824 4855.9542) (2659.8626 4859.8168) (2660.7634 4864.3817) (2659.8626 4868.9313)
      (2657.2824 4872.7939) (2653.4046 4875.374) (2648.855 4876.2901) (2644.3053 4875.374) (2640.4275 4872.7939)
      (2637.8473 4868.9313)
    ))
    ; P2362 -- see feature_dimensions_mm.csv
    ("06_ORNAMENT" 1 (
      (2636.9466 4552.9313) (2637.8473 4548.3664) (2640.4275 4544.5038) (2644.3053 4541.9237) (2648.855 4541.0229)
      (2653.4046 4541.9237) (2657.2824 4544.5038) (2659.8626 4548.3664) (2660.7634 4552.9313) (2659.8626 4557.4809)
      (2657.2824 4561.3435) (2653.4046 4563.9237) (2648.855 4564.8397) (2644.3053 4563.9237) (2640.4275 4561.3435)
      (2637.8473 4557.4809)
    ))
    ; P2363 -- see feature_dimensions_mm.csv
    ("06_ORNAMENT" 1 (
      (2636.9466 4241.4809) (2637.8473 4236.916) (2640.4275 4233.0534) (2644.3053 4230.4733) (2648.855 4229.5725)
      (2653.4046 4230.4733) (2657.2824 4233.0534) (2659.8626 4236.916) (2660.7634 4241.4809) (2659.8626 4246.0305)
      (2657.2824 4249.8931) (2653.4046 4252.4733) (2648.855 4253.3893) (2644.3053 4252.4733) (2640.4275 4249.8931)
      (2637.8473 4246.0305)
    ))
    ; P2364 -- see feature_dimensions_mm.csv
    ("06_ORNAMENT" 1 (
      (2636.9466 3930.0305) (2637.8473 3925.4656) (2640.4275 3921.6031) (2644.3053 3919.0229) (2648.855 3918.1221)
      (2653.4046 3919.0229) (2657.2824 3921.6031) (2659.8626 3925.4656) (2660.7634 3930.0305) (2659.8626 3934.5802)
      (2657.2824 3938.4427) (2653.4046 3941.0229) (2648.855 3941.9389) (2644.3053 3941.0229) (2640.4275 3938.4427)
      (2637.8473 3934.5802)
    ))
    ; P2365 -- see feature_dimensions_mm.csv
    ("06_ORNAMENT" 1 (
      (2677.0992 5331.5573) (2678.7939 5328.4122) (2683.4198 5325.8626) (2689.7252 5324.1985) (2696.0458 5323.3282)
      (2700.7786 5322.7481) (2702.8855 5321.6794) (2702.1527 5319.4351) (2699.2214 5315.6794) (2695.3588 5310.6107)
      (2692.0763 5304.9771) (2690.6107 5299.8931) (2691.6336 5296.4733) (2695.0534 5295.4504) (2700.1374 5296.916)
      (2705.771 5300.1985) (2710.8397 5304.0458) (2714.5954 5306.9771) (2716.8397 5307.7099) (2717.9084 5305.6183)
      (2718.5038 5300.8855) (2719.3588 5294.5649) (2721.0229 5288.2595) (2723.5725 5283.6336) (2726.7176 5281.9389)
      (2729.8626 5283.6336) (2732.4122 5288.2595) (2734.0763 5294.5649) (2734.9313 5300.8855) (2735.5267 5305.6183)
      (2736.5954 5307.7099) (2738.8397 5306.9771) (2742.5954 5304.0458) (2747.6641 5300.1985) (2753.2977 5296.916)
      (2758.3817 5295.4504) (2761.8015 5296.4733) (2762.8244 5299.8931) (2761.3588 5304.9771) (2758.0763 5310.6107)
      (2754.2137 5315.6794) (2751.2824 5319.4351) (2750.5496 5321.6794) (2752.6565 5322.7481) (2757.3893 5323.3282)
      (2763.7099 5324.1985) (2770.0153 5325.8626) (2774.6412 5328.4122) (2776.3359 5331.5573) (2774.6412 5334.7023)
      (2770.0153 5337.2519) (2763.7099 5338.916) (2757.3893 5339.771) (2752.6565 5340.3664) (2750.5496 5341.4351)
      (2751.2824 5343.6794) (2754.2137 5347.4351) (2758.0763 5352.5038) (2761.3588 5358.1374) (2762.8244 5363.2214)
      (2761.8015 5366.6412) (2758.3817 5367.6641) (2753.2977 5366.1985) (2747.6641 5362.916) (2742.5954 5359.0534)
      (2738.8397 5356.1221) (2736.5954 5355.3893) (2735.5267 5357.4962) (2734.9313 5362.229) (2734.0763 5368.5344)
      (2732.4122 5374.8397) (2729.8626 5379.4809) (2726.7176 5381.1756) (2723.5725 5379.4809) (2721.0229 5374.8397)
      (2719.3588 5368.5344) (2718.5038 5362.229) (2717.9084 5357.4962) (2716.8397 5355.3893) (2714.5954 5356.1221)
      (2710.8397 5359.0534) (2705.771 5362.916) (2700.1374 5366.1985) (2695.0534 5367.6641) (2691.6336 5366.6412)
      (2690.6107 5363.2214) (2692.0763 5358.1374) (2695.3588 5352.5038) (2699.2214 5347.4351) (2702.1527 5343.6794)
      (2702.8855 5341.4351) (2700.7786 5340.3664) (2696.0458 5339.771) (2689.7252 5338.916) (2683.4198 5337.2519)
      (2678.7939 5334.7023)
    ))
    ; P2366 -- see feature_dimensions_mm.csv
    ("06_ORNAMENT" 1 (
      (2677.0992 5020.1069) (2678.7939 5016.9618) (2683.4198 5014.4122) (2689.7252 5012.7481) (2696.0458 5011.8779)
      (2700.7786 5011.2977) (2702.8855 5010.229) (2702.1527 5007.9847) (2699.2214 5004.229) (2695.3588 4999.1603)
      (2692.0763 4993.5267) (2690.6107 4988.4427) (2691.6336 4985.0229) (2695.0534 4984.0) (2700.1374 4985.4656)
      (2705.771 4988.7481) (2710.8397 4992.5954) (2714.5954 4995.5267) (2716.8397 4996.2595) (2717.9084 4994.1679)
      (2718.5038 4989.4351) (2719.3588 4983.1145) (2721.0229 4976.8092) (2723.5725 4972.1832) (2726.7176 4970.4885)
      (2729.8626 4972.1832) (2732.4122 4976.8092) (2734.0763 4983.1145) (2734.9313 4989.4351) (2735.5267 4994.1679)
      (2736.5954 4996.2595) (2738.8397 4995.5267) (2742.5954 4992.5954) (2747.6641 4988.7481) (2753.2977 4985.4656)
      (2758.3817 4984.0) (2761.8015 4985.0229) (2762.8244 4988.4427) (2761.3588 4993.5267) (2758.0763 4999.1603)
      (2754.2137 5004.229) (2751.2824 5007.9847) (2750.5496 5010.229) (2752.6565 5011.2977) (2757.3893 5011.8779)
      (2763.7099 5012.7481) (2770.0153 5014.4122) (2774.6412 5016.9618) (2776.3359 5020.1069) (2774.6412 5023.2519)
      (2770.0153 5025.8015) (2763.7099 5027.4656) (2757.3893 5028.3206) (2752.6565 5028.916) (2750.5496 5029.9847)
      (2751.2824 5032.229) (2754.2137 5035.9847) (2758.0763 5041.0534) (2761.3588 5046.687) (2762.8244 5051.771)
      (2761.8015 5055.1908) (2758.3817 5056.2137) (2753.2977 5054.7481) (2747.6641 5051.4656) (2742.5954 5047.6031)
      (2738.8397 5044.6718) (2736.5954 5043.9389) (2735.5267 5046.0458) (2734.9313 5050.7786) (2734.0763 5057.084)
      (2732.4122 5063.3893) (2729.8626 5068.0305) (2726.7176 5069.7252) (2723.5725 5068.0305) (2721.0229 5063.3893)
      (2719.3588 5057.084) (2718.5038 5050.7786) (2717.9084 5046.0458) (2716.8397 5043.9389) (2714.5954 5044.6718)
      (2710.8397 5047.6031) (2705.771 5051.4656) (2700.1374 5054.7481) (2695.0534 5056.2137) (2691.6336 5055.1908)
      (2690.6107 5051.771) (2692.0763 5046.687) (2695.3588 5041.0534) (2699.2214 5035.9847) (2702.1527 5032.229)
      (2702.8855 5029.9847) (2700.7786 5028.916) (2696.0458 5028.3206) (2689.7252 5027.4656) (2683.4198 5025.8015)
      (2678.7939 5023.2519)
    ))
    ; P2367 -- see feature_dimensions_mm.csv
    ("06_ORNAMENT" 1 (
      (2677.0992 4708.6565) (2678.7939 4705.5115) (2683.4198 4702.9618) (2689.7252 4701.2977) (2696.0458 4700.4275)
      (2700.7786 4699.8473) (2702.8855 4698.7786) (2702.1527 4696.5344) (2699.2214 4692.7786) (2695.3588 4687.7099)
      (2692.0763 4682.0763) (2690.6107 4676.9924) (2691.6336 4673.5725) (2695.0534 4672.5496) (2700.1374 4674.0153)
      (2705.771 4677.2977) (2710.8397 4681.145) (2714.5954 4684.0763) (2716.8397 4684.8092) (2717.9084 4682.7176)
      (2718.5038 4677.9847) (2719.3588 4671.6641) (2721.0229 4665.3588) (2723.5725 4660.7328) (2726.7176 4659.0382)
      (2729.8626 4660.7328) (2732.4122 4665.3588) (2734.0763 4671.6641) (2734.9313 4677.9847) (2735.5267 4682.7176)
      (2736.5954 4684.8092) (2738.8397 4684.0763) (2742.5954 4681.145) (2747.6641 4677.2977) (2753.2977 4674.0153)
      (2758.3817 4672.5496) (2761.8015 4673.5725) (2762.8244 4676.9924) (2761.3588 4682.0763) (2758.0763 4687.7099)
      (2754.2137 4692.7786) (2751.2824 4696.5344) (2750.5496 4698.7786) (2752.6565 4699.8473) (2757.3893 4700.4275)
      (2763.7099 4701.2977) (2770.0153 4702.9618) (2774.6412 4705.5115) (2776.3359 4708.6565) (2774.6412 4711.8015)
      (2770.0153 4714.3511) (2763.7099 4716.0153) (2757.3893 4716.8702) (2752.6565 4717.4656) (2750.5496 4718.5344)
      (2751.2824 4720.7786) (2754.2137 4724.5344) (2758.0763 4729.6031) (2761.3588 4735.2366) (2762.8244 4740.3206)
      (2761.8015 4743.7405) (2758.3817 4744.7634) (2753.2977 4743.2977) (2747.6641 4740.0153) (2742.5954 4736.1527)
      (2738.8397 4733.2214) (2736.5954 4732.4885) (2735.5267 4734.5954) (2734.9313 4739.3282) (2734.0763 4745.6336)
      (2732.4122 4751.9389) (2729.8626 4756.5802) (2726.7176 4758.2748) (2723.5725 4756.5802) (2721.0229 4751.9389)
      (2719.3588 4745.6336) (2718.5038 4739.3282) (2717.9084 4734.5954) (2716.8397 4732.4885) (2714.5954 4733.2214)
      (2710.8397 4736.1527) (2705.771 4740.0153) (2700.1374 4743.2977) (2695.0534 4744.7634) (2691.6336 4743.7405)
      (2690.6107 4740.3206) (2692.0763 4735.2366) (2695.3588 4729.6031) (2699.2214 4724.5344) (2702.1527 4720.7786)
      (2702.8855 4718.5344) (2700.7786 4717.4656) (2696.0458 4716.8702) (2689.7252 4716.0153) (2683.4198 4714.3511)
      (2678.7939 4711.8015)
    ))
    ; P2368 -- see feature_dimensions_mm.csv
    ("06_ORNAMENT" 1 (
      (2677.0992 4397.2061) (2678.7939 4394.0611) (2683.4198 4391.5115) (2689.7252 4389.8473) (2696.0458 4388.9771)
      (2700.7786 4388.3969) (2702.8855 4387.3282) (2702.1527 4385.084) (2699.2214 4381.3282) (2695.3588 4376.2595)
      (2692.0763 4370.626) (2690.6107 4365.542) (2691.6336 4362.1221) (2695.0534 4361.0992) (2700.1374 4362.5649)
      (2705.771 4365.8473) (2710.8397 4369.6947) (2714.5954 4372.626) (2716.8397 4373.3588) (2717.9084 4371.2672)
      (2718.5038 4366.5344) (2719.3588 4360.2137) (2721.0229 4353.9084) (2723.5725 4349.2824) (2726.7176 4347.5878)
      (2729.8626 4349.2824) (2732.4122 4353.9084) (2734.0763 4360.2137) (2734.9313 4366.5344) (2735.5267 4371.2672)
      (2736.5954 4373.3588) (2738.8397 4372.626) (2742.5954 4369.6947) (2747.6641 4365.8473) (2753.2977 4362.5649)
      (2758.3817 4361.0992) (2761.8015 4362.1221) (2762.8244 4365.542) (2761.3588 4370.626) (2758.0763 4376.2595)
      (2754.2137 4381.3282) (2751.2824 4385.084) (2750.5496 4387.3282) (2752.6565 4388.3969) (2757.3893 4388.9771)
      (2763.7099 4389.8473) (2770.0153 4391.5115) (2774.6412 4394.0611) (2776.3359 4397.2061) (2774.6412 4400.3511)
      (2770.0153 4402.9008) (2763.7099 4404.5649) (2757.3893 4405.4198) (2752.6565 4406.0153) (2750.5496 4407.084)
      (2751.2824 4409.3282) (2753.542 4412.2137) (2699.8931 4412.2137) (2702.1527 4409.3282) (2702.8855 4407.084)
      (2700.7786 4406.0153) (2696.0458 4405.4198) (2689.7252 4404.5649) (2683.4198 4402.9008) (2678.7939 4400.3511)
    ))
    ; P2369 -- see feature_dimensions_mm.csv
    ("06_ORNAMENT" 1 (
      (2677.0992 4085.7557) (2678.7939 4082.6107) (2683.4198 4080.0611) (2689.7252 4078.3969) (2696.0458 4077.5267)
      (2700.7786 4076.9466) (2702.8855 4075.8779) (2702.1527 4073.6336) (2699.2214 4069.8779) (2695.3588 4064.8092)
      (2692.0763 4059.1756) (2690.6107 4054.0916) (2691.6336 4050.6718) (2695.0534 4049.6489) (2700.1374 4051.1145)
      (2705.771 4054.3969) (2710.8397 4058.2595) (2714.5954 4061.1756) (2716.8397 4061.9084) (2717.9084 4059.8168)
      (2718.5038 4055.084) (2719.3588 4048.7634) (2721.0229 4042.458) (2723.5725 4037.8321) (2726.7176 4036.1374)
      (2729.8626 4037.8321) (2732.4122 4042.458) (2734.0763 4048.7634) (2734.9313 4055.084) (2735.5267 4059.8168)
      (2736.5954 4061.9084) (2738.8397 4061.1756) (2742.5954 4058.2595) (2747.6641 4054.3969) (2753.2977 4051.1145)
      (2758.3817 4049.6489) (2761.8015 4050.6718) (2762.8244 4054.0916) (2761.3588 4059.1756) (2758.0763 4064.8092)
      (2754.2137 4069.8779) (2751.2824 4073.6336) (2750.5496 4075.8779) (2752.6565 4076.9466) (2757.3893 4077.5267)
      (2763.7099 4078.3969) (2770.0153 4080.0611) (2774.6412 4082.6107) (2776.3359 4085.7557) (2774.6412 4088.9008)
      (2770.0153 4091.4504) (2763.7099 4093.1145) (2757.3893 4093.9695) (2752.6565 4094.5649) (2750.5496 4095.6336)
      (2751.2824 4097.8779) (2754.2137 4101.6336) (2758.0763 4106.7023) (2761.3588 4112.3359) (2762.8244 4117.4198)
      (2761.8015 4120.8397) (2758.3817 4121.8626) (2753.2977 4120.3969) (2747.6641 4117.1145) (2742.5954 4113.2519)
      (2738.8397 4110.3206) (2736.5954 4109.5878) (2735.5267 4111.6947) (2734.9313 4116.4275) (2734.0763 4122.7328)
      (2732.4122 4129.0382) (2729.8626 4133.6794) (2726.7176 4135.374) (2723.5725 4133.6794) (2721.0229 4129.0382)
      (2719.3588 4122.7328) (2718.5038 4116.4275) (2717.9084 4111.6947) (2716.8397 4109.5878) (2714.5954 4110.3206)
      (2710.8397 4113.2519) (2705.771 4117.1145) (2700.1374 4120.3969) (2695.0534 4121.8626) (2691.6336 4120.8397)
      (2690.6107 4117.4198) (2692.0763 4112.3359) (2695.3588 4106.7023) (2699.2214 4101.6336) (2702.1527 4097.8779)
      (2702.8855 4095.6336) (2700.7786 4094.5649) (2696.0458 4093.9695) (2689.7252 4093.1145) (2683.4198 4091.4504)
      (2678.7939 4088.9008)
    ))
    ; P2370 -- see feature_dimensions_mm.csv
    ("06_ORNAMENT" 1 (
      (2678.9313 5874.4885) (2691.7863 5856.8244) (2706.916 5841.0382) (2724.0 5827.0992) (2742.687 5814.9771)
      (2752.8092 5809.7252) (2761.1298 5811.4656) (2761.7863 5811.6031) (2808.8244 5820.7481) (2809.4351 5820.8702)
      (2847.9542 5827.8321) (2840.2137 5864.4122) (2826.1221 5870.3817) (2804.9466 5877.4962) (2783.4198 5882.7939)
      (2761.8015 5886.0458) (2740.3053 5887.0534) (2738.7481 5886.9466) (2742.8244 5888.3969) (2762.8855 5898.0611)
      (2782.1069 5909.7557) (2800.3053 5923.1756) (2817.3435 5938.0305) (2833.0687 5954.0) (2847.3435 5970.8092)
      (2860.0305 5988.1527) (2870.9466 6005.7252) (2879.9542 6023.2366) (2885.771 6037.542) (2887.4351 6037.0382)
      (2899.8168 6034.8397) (2910.4885 6033.4809) (2918.1374 6031.9847) (2922.0916 6029.313) (2922.4427 6024.5496)
      (2919.9084 6017.1756) (2915.7405 6007.2672) (2911.4656 5995.4351) (2908.5038 5982.8397) (2907.9695 5970.9771)
      (2910.4885 5961.374) (2916.0305 5955.2977) (2924.0611 5953.5267) (2933.6489 5956.1679) (2943.6489 5962.5496)
      (2953.0687 5971.4046) (2961.1756 5981.0229) (2967.6947 5989.5878) (2972.7939 5995.4656) (2977.0992 5997.5573)
      (2981.4046 5995.4656) (2983.542 5993.0076) (2980.5496 5991.0076) (2963.5267 5977.2824) (2948.2595 5962.1221)
      (2935.0382 5945.5725) (2931.0229 5938.9313) (3055.8321 5938.9313) (3064.1832 5943.7099) (3082.7328 5956.3053)
      (3100.0153 5970.0153) (3115.8168 5984.5496) (3129.9695 5999.6489) (3142.229 6015.084) (3152.4122 6030.5496)
      (3160.3053 6045.8015) (3141.7405 6046.1679) (3122.0916 6044.8702) (3101.6794 6041.8931) (3080.7939 6037.313)
      (3059.771 6031.1298) (3038.9313 6023.374) (3033.084 6020.7176) (3031.7557 6024.5496) (3032.1069 6029.313)
      (3036.0611 6031.9847) (3043.7099 6033.4809) (3054.3817 6034.8397) (3066.7634 6037.0382) (3079.145 6040.7786)
      (3089.6794 6046.2443) (3096.7481 6053.2214) (3099.2366 6061.0687) (3096.7481 6068.916) (3089.6794 6075.8931)
      (3079.145 6081.3588) (3066.7634 6085.0992) (3054.3817 6087.2977) (3043.7099 6088.6565) (3036.0611 6090.1527)
      (3032.1069 6092.8244) (3031.7557 6097.5878) (3034.3053 6104.9618) (3038.458 6114.8702) (3042.7328 6126.7023)
      (3045.6947 6139.2977) (3046.229 6151.1603) (3043.7099 6160.7634) (3038.1679 6166.8397) (3030.1374 6168.6107)
      (3020.5496 6165.9695) (3010.5496 6159.5878) (3001.1298 6150.7328) (2993.0229 6141.1145) (2986.5038 6132.5496)
      (2981.4046 6126.6718) (2977.0992 6124.5802) (2972.7939 6126.6718) (2967.6947 6132.5496) (2961.1756 6141.1145)
      (2953.0687 6150.7328) (2943.6489 6159.5878) (2933.6489 6165.9695) (2924.0611 6168.6107) (2916.0305 6166.8397)
      (2910.4885 6160.7634) (2907.9695 6151.1603) (2908.5038 6139.2977) (2911.4656 6126.7023) (2915.7405 6114.8702)
      (2919.9084 6104.9618) (2922.4427 6097.5878) (2922.0916 6092.8244) (2918.1374 6090.1527) (2910.4885 6088.6565)
      (2899.8168 6087.2977) (2887.4351 6085.0992) (2875.0534 6081.3588) (2864.5191 6075.8931) (2857.4504 6068.916)
      (2854.9618 6061.0687) (2857.4504 6053.2214) (2860.5344 6050.1832) (2854.4122 6048.5191) (2834.9618 6041.6336)
      (2815.374 6033.0687) (2795.9695 6022.9008) (2777.0382 6011.2366) (2758.8702 5998.1527) (2741.7863 5983.7405)
      (2726.0916 5968.0916) (2712.0763 5951.313) (2700.0458 5933.4656) (2690.3206 5914.6565) (2683.1756 5894.9618)
    ))
    ; P2371 -- see feature_dimensions_mm.csv
    ("06_ORNAMENT" 1 (
      (2687.0229 7374.0458) (2748.0916 7343.5115) (2809.1603 7374.0458) (2748.0916 7404.5802)
    ))
    ; P2372 -- see feature_dimensions_mm.csv
    ("06_ORNAMENT" 1 (
      (2687.0229 7282.4427) (2748.0916 7251.9084) (2809.1603 7282.4427) (2748.0916 7312.9771)
    ))
    ; P2373 -- see feature_dimensions_mm.csv
    ("06_ORNAMENT" 1 (
      (2687.0229 7190.8397) (2748.0916 7160.3053) (2809.1603 7190.8397) (2748.0916 7221.374)
    ))
    ; P2374 -- see feature_dimensions_mm.csv
    ("06_ORNAMENT" 1 (
      (2708.3969 5409.4198) (2726.7176 5388.8092) (2745.0382 5409.4198) (2726.7176 5430.0305)
    ))
    ; P2375 -- see feature_dimensions_mm.csv
    ("06_ORNAMENT" 1 (
      (2708.3969 5097.9695) (2726.7176 5077.3588) (2745.0382 5097.9695) (2726.7176 5118.5802)
    ))
    ; P2376 -- see feature_dimensions_mm.csv
    ("06_ORNAMENT" 1 (
      (2708.3969 4786.5191) (2726.7176 4765.9084) (2745.0382 4786.5191) (2726.7176 4807.1298)
    ))
    ; P2377 -- see feature_dimensions_mm.csv
    ("06_ORNAMENT" 1 (
      (2708.3969 4163.6183) (2726.7176 4143.0076) (2745.0382 4163.6183) (2726.7176 4184.229)
    ))
    ; P2378 -- see feature_dimensions_mm.csv
    ("06_ORNAMENT" 1 (
      (2714.8092 5331.5573) (2715.7099 5326.9924) (2718.2901 5323.1298) (2722.1679 5320.5496) (2726.7176 5319.6489)
      (2731.2672 5320.5496) (2735.145 5323.1298) (2737.7252 5326.9924) (2738.626 5331.5573) (2737.7252 5336.1069)
      (2735.145 5339.9695) (2731.2672 5342.5496) (2726.7176 5343.4656) (2722.1679 5342.5496) (2718.2901 5339.9695)
      (2715.7099 5336.1069)
    ))
    ; P2379 -- see feature_dimensions_mm.csv
    ("06_ORNAMENT" 1 (
      (2714.8092 5020.1069) (2715.7099 5015.542) (2718.2901 5011.6794) (2722.1679 5009.0992) (2726.7176 5008.1985)
      (2731.2672 5009.0992) (2735.145 5011.6794) (2737.7252 5015.542) (2738.626 5020.1069) (2737.7252 5024.6565)
      (2735.145 5028.5191) (2731.2672 5031.0992) (2726.7176 5032.0153) (2722.1679 5031.0992) (2718.2901 5028.5191)
      (2715.7099 5024.6565)
    ))
    ; P2380 -- see feature_dimensions_mm.csv
    ("06_ORNAMENT" 1 (
      (2714.8092 4708.6565) (2715.7099 4704.0916) (2718.2901 4700.229) (2722.1679 4697.6489) (2726.7176 4696.7481)
      (2731.2672 4697.6489) (2735.145 4700.229) (2737.7252 4704.0916) (2738.626 4708.6565) (2737.7252 4713.2061)
      (2735.145 4717.0687) (2731.2672 4719.6489) (2726.7176 4720.5649) (2722.1679 4719.6489) (2718.2901 4717.0687)
      (2715.7099 4713.2061)
    ))
    ; P2381 -- see feature_dimensions_mm.csv
    ("06_ORNAMENT" 1 (
      (2714.8092 4397.2061) (2715.7099 4392.6412) (2718.2901 4388.7786) (2722.1679 4386.1985) (2726.7176 4385.2977)
      (2731.2672 4386.1985) (2735.145 4388.7786) (2737.7252 4392.6412) (2738.626 4397.2061) (2737.7252 4401.7557)
      (2735.145 4405.6183) (2731.2672 4408.1985) (2726.7176 4409.1145) (2722.1679 4408.1985) (2718.2901 4405.6183)
      (2715.7099 4401.7557)
    ))
    ; P2382 -- see feature_dimensions_mm.csv
    ("06_ORNAMENT" 1 (
      (2714.8092 4085.7557) (2715.7099 4081.1908) (2718.2901 4077.3282) (2722.1679 4074.7481) (2726.7176 4073.8473)
      (2731.2672 4074.7481) (2735.145 4077.3282) (2737.7252 4081.1908) (2738.626 4085.7557) (2737.7252 4090.3053)
      (2735.145 4094.1679) (2731.2672 4096.7481) (2726.7176 4097.6641) (2722.1679 4096.7481) (2718.2901 4094.1679)
      (2715.7099 4090.3053)
    ))
    ; P2383 -- see feature_dimensions_mm.csv
    ("06_ORNAMENT" 1 (
      (2754.9618 5487.2824) (2756.6565 5484.1374) (2761.2824 5481.5878) (2767.5878 5479.9237) (2773.9084 5479.0534)
      (2778.6412 5478.4733) (2780.7481 5477.4046) (2780.0153 5475.1603) (2777.084 5471.4046) (2773.2214 5466.3359)
      (2769.9389 5460.7023) (2768.4733 5455.6183) (2769.4962 5452.1985) (2772.916 5451.1756) (2778.0 5452.6412)
      (2783.6336 5455.9237) (2788.7023 5459.771) (2792.458 5462.7023) (2794.7023 5463.4351) (2795.771 5461.3435)
      (2796.3664 5456.6107) (2797.2214 5450.2901) (2798.8855 5443.9847) (2801.4351 5439.3588) (2804.5802 5437.6641)
      (2807.7252 5439.3588) (2810.2748 5443.9847) (2811.9389 5450.2901) (2812.7939 5456.6107) (2813.3893 5461.3435)
      (2814.458 5463.4351) (2816.7023 5462.7023) (2820.458 5459.771) (2825.5267 5455.9237) (2831.1603 5452.6412)
      (2836.2443 5451.1756) (2839.6641 5452.1985) (2840.687 5455.6183) (2839.2214 5460.7023) (2835.9389 5466.3359)
      (2832.0763 5471.4046) (2829.145 5475.1603) (2828.4122 5477.4046) (2830.5191 5478.4733) (2835.2519 5479.0534)
      (2841.5725 5479.9237) (2847.8779 5481.5878) (2852.5038 5484.1374) (2854.1985 5487.2824) (2852.5038 5490.4275)
      (2847.8779 5492.9771) (2841.5725 5494.6412) (2835.2519 5495.4962) (2830.5191 5496.0916) (2828.4122 5497.1603)
      (2829.145 5499.4046) (2832.0763 5503.1603) (2835.9389 5508.229) (2839.2214 5513.8626) (2840.687 5518.9466)
      (2839.6641 5522.3664) (2836.2443 5523.3893) (2831.1603 5521.9237) (2825.5267 5518.6412) (2820.458 5514.7786)
      (2816.7023 5511.8473) (2814.458 5511.1145) (2813.3893 5513.2214) (2812.7939 5517.9542) (2811.9389 5524.2595)
      (2810.2748 5530.5649) (2807.7252 5535.2061) (2804.5802 5536.9008) (2801.4351 5535.2061) (2798.8855 5530.5649)
      (2797.2214 5524.2595) (2796.3664 5517.9542) (2795.771 5513.2214) (2794.7023 5511.1145) (2792.458 5511.8473)
      (2788.7023 5514.7786) (2783.6336 5518.6412) (2778.0 5521.9237) (2772.916 5523.3893) (2769.4962 5522.3664)
      (2768.4733 5518.9466) (2769.9389 5513.8626) (2773.2214 5508.229) (2777.084 5503.1603) (2780.0153 5499.4046)
      (2780.7481 5497.1603) (2778.6412 5496.0916) (2773.9084 5495.4962) (2767.5878 5494.6412) (2761.2824 5492.9771)
      (2756.6565 5490.4275)
    ))
    ; P2384 -- see feature_dimensions_mm.csv
    ("06_ORNAMENT" 1 (
      (2754.9618 5175.8321) (2756.6565 5172.687) (2761.2824 5170.1374) (2767.5878 5168.4733) (2773.9084 5167.6031)
      (2778.6412 5167.0229) (2780.7481 5165.9542) (2780.0153 5163.7099) (2777.084 5159.9542) (2773.2214 5154.8855)
      (2769.9389 5149.2519) (2768.4733 5144.1679) (2769.4962 5140.7481) (2772.916 5139.7252) (2778.0 5141.1908)
      (2783.6336 5144.4733) (2788.7023 5148.3206) (2792.458 5151.2519) (2794.7023 5151.9847) (2795.771 5149.8931)
      (2796.3664 5145.1603) (2797.2214 5138.8397) (2798.8855 5132.5344) (2801.4351 5127.9084) (2804.5802 5126.2137)
      (2807.7252 5127.9084) (2810.2748 5132.5344) (2811.9389 5138.8397) (2812.7939 5145.1603) (2813.3893 5149.8931)
      (2814.458 5151.9847) (2816.7023 5151.2519) (2820.458 5148.3206) (2825.5267 5144.4733) (2831.1603 5141.1908)
      (2836.2443 5139.7252) (2839.6641 5140.7481) (2840.687 5144.1679) (2839.2214 5149.2519) (2835.9389 5154.8855)
      (2832.0763 5159.9542) (2829.145 5163.7099) (2828.4122 5165.9542) (2830.5191 5167.0229) (2835.2519 5167.6031)
      (2841.5725 5168.4733) (2847.8779 5170.1374) (2852.5038 5172.687) (2854.1985 5175.8321) (2852.5038 5178.9771)
      (2847.8779 5181.5267) (2841.5725 5183.1908) (2835.2519 5184.0458) (2830.5191 5184.6412) (2828.4122 5185.7099)
      (2829.145 5187.9542) (2832.0763 5191.7099) (2835.9389 5196.7786) (2839.2214 5202.4122) (2840.687 5207.4962)
      (2839.6641 5210.916) (2836.2443 5211.9389) (2831.1603 5210.4733) (2825.5267 5207.1908) (2820.458 5203.3282)
      (2816.7023 5200.3969) (2814.458 5199.6641) (2813.3893 5201.771) (2812.7939 5206.5038) (2811.9389 5212.8092)
      (2810.2748 5219.1145) (2807.7252 5223.7557) (2804.5802 5225.4504) (2801.4351 5223.7557) (2798.8855 5219.1145)
      (2797.2214 5212.8092) (2796.3664 5206.5038) (2795.771 5201.771) (2794.7023 5199.6641) (2792.458 5200.3969)
      (2788.7023 5203.3282) (2783.6336 5207.1908) (2778.0 5210.4733) (2772.916 5211.9389) (2769.4962 5210.916)
      (2768.4733 5207.4962) (2769.9389 5202.4122) (2773.2214 5196.7786) (2777.084 5191.7099) (2780.0153 5187.9542)
      (2780.7481 5185.7099) (2778.6412 5184.6412) (2773.9084 5184.0458) (2767.5878 5183.1908) (2761.2824 5181.5267)
      (2756.6565 5178.9771)
    ))
    ; P2385 -- see feature_dimensions_mm.csv
    ("06_ORNAMENT" 1 (
      (2754.9618 4864.3817) (2756.6565 4861.2366) (2761.2824 4858.687) (2767.5878 4857.0229) (2773.9084 4856.1527)
      (2778.6412 4855.5725) (2780.7481 4854.5038) (2780.0153 4852.2595) (2777.084 4848.5038) (2773.2214 4843.4351)
      (2769.9389 4837.8015) (2768.4733 4832.7176) (2769.4962 4829.2977) (2772.916 4828.2748) (2778.0 4829.7405)
      (2783.6336 4833.0229) (2788.7023 4836.8702) (2792.458 4839.8015) (2794.7023 4840.5344) (2795.771 4838.4427)
      (2796.3664 4833.7099) (2797.2214 4827.3893) (2798.8855 4821.084) (2801.4351 4816.458) (2804.5802 4814.7634)
      (2807.7252 4816.458) (2810.2748 4821.084) (2811.9389 4827.3893) (2812.7939 4833.7099) (2813.3893 4838.4427)
      (2814.458 4840.5344) (2816.7023 4839.8015) (2820.458 4836.8702) (2825.5267 4833.0229) (2831.1603 4829.7405)
      (2836.2443 4828.2748) (2839.6641 4829.2977) (2840.687 4832.7176) (2839.2214 4837.8015) (2835.9389 4843.4351)
      (2832.0763 4848.5038) (2829.145 4852.2595) (2828.4122 4854.5038) (2830.5191 4855.5725) (2835.2519 4856.1527)
      (2841.5725 4857.0229) (2847.8779 4858.687) (2852.5038 4861.2366) (2854.1985 4864.3817) (2852.5038 4867.5267)
      (2847.8779 4870.0763) (2841.5725 4871.7405) (2835.2519 4872.5954) (2830.5191 4873.1908) (2828.4122 4874.2595)
      (2829.145 4876.5038) (2832.0763 4880.2595) (2835.9389 4885.3282) (2839.2214 4890.9618) (2840.687 4896.0458)
      (2839.6641 4899.4656) (2836.2443 4900.4885) (2831.1603 4899.0229) (2825.5267 4895.7405) (2820.458 4891.8779)
      (2816.7023 4888.9466) (2814.458 4888.2137) (2813.3893 4890.3206) (2812.7939 4895.0534) (2811.9389 4901.3588)
      (2810.2748 4907.6641) (2807.7252 4912.3053) (2804.5802 4914.0) (2801.4351 4912.3053) (2798.8855 4907.6641)
      (2797.2214 4901.3588) (2796.3664 4895.0534) (2795.771 4890.3206) (2794.7023 4888.2137) (2792.458 4888.9466)
      (2788.7023 4891.8779) (2783.6336 4895.7405) (2778.0 4899.0229) (2772.916 4900.4885) (2769.4962 4899.4656)
      (2768.4733 4896.0458) (2769.9389 4890.9618) (2773.2214 4885.3282) (2777.084 4880.2595) (2780.0153 4876.5038)
      (2780.7481 4874.2595) (2778.6412 4873.1908) (2773.9084 4872.5954) (2767.5878 4871.7405) (2761.2824 4870.0763)
      (2756.6565 4867.5267)
    ))
    ; P2386 -- see feature_dimensions_mm.csv
    ("06_ORNAMENT" 1 (
      (2754.9618 4552.9313) (2756.6565 4549.7863) (2761.2824 4547.2366) (2767.5878 4545.5725) (2773.9084 4544.7023)
      (2778.6412 4544.1221) (2780.7481 4543.0534) (2780.0153 4540.8092) (2777.084 4537.0534) (2773.2214 4531.9847)
      (2769.9389 4526.3511) (2768.4733 4521.2672) (2769.4962 4517.8473) (2772.916 4516.8244) (2778.0 4518.2901)
      (2783.6336 4521.5725) (2788.7023 4525.4198) (2792.458 4528.3511) (2794.7023 4529.084) (2795.771 4526.9924)
      (2796.3664 4522.2595) (2797.2214 4515.9389) (2798.8855 4509.6336) (2801.4351 4505.0076) (2804.5802 4503.313)
      (2807.7252 4505.0076) (2810.2748 4509.6336) (2811.9389 4515.9389) (2812.7939 4522.2595) (2813.3893 4526.9924)
      (2814.458 4529.084) (2816.7023 4528.3511) (2820.458 4525.4198) (2825.5267 4521.5725) (2831.1603 4518.2901)
      (2836.2443 4516.8244) (2839.6641 4517.8473) (2840.687 4521.2672) (2839.2214 4526.3511) (2835.9389 4531.9847)
      (2832.0763 4537.0534) (2829.145 4540.8092) (2828.4122 4543.0534) (2830.5191 4544.1221) (2835.2519 4544.7023)
      (2841.5725 4545.5725) (2847.8779 4547.2366) (2852.5038 4549.7863) (2854.1985 4552.9313) (2852.5038 4556.0763)
      (2847.8779 4558.626) (2841.5725 4560.2901) (2835.2519 4561.145) (2830.5191 4561.7405) (2828.4122 4562.8092)
      (2829.145 4565.0534) (2832.0763 4568.8092) (2835.9389 4573.8779) (2839.2214 4579.5115) (2840.687 4584.5954)
      (2839.6641 4588.0153) (2836.2443 4589.0382) (2831.1603 4587.5725) (2825.5267 4584.2901) (2820.458 4580.4275)
      (2816.7023 4577.4962) (2814.458 4576.7634) (2813.3893 4578.8702) (2812.7939 4583.6031) (2811.9389 4589.9084)
      (2810.2748 4596.2137) (2807.7252 4600.855) (2804.5802 4602.5496) (2801.4351 4600.855) (2798.8855 4596.2137)
      (2797.2214 4589.9084) (2796.3664 4583.6031) (2795.771 4578.8702) (2794.7023 4576.7634) (2792.458 4577.4962)
      (2788.7023 4580.4275) (2783.6336 4584.2901) (2778.0 4587.5725) (2772.916 4589.0382) (2769.4962 4588.0153)
      (2768.4733 4584.5954) (2769.9389 4579.5115) (2773.2214 4573.8779) (2777.084 4568.8092) (2780.0153 4565.0534)
      (2780.7481 4562.8092) (2778.6412 4561.7405) (2773.9084 4561.145) (2767.5878 4560.2901) (2761.2824 4558.626)
      (2756.6565 4556.0763)
    ))
    ; P2387 -- see feature_dimensions_mm.csv
    ("06_ORNAMENT" 1 (
      (2754.9618 4241.4809) (2756.6565 4238.3359) (2761.2824 4235.7863) (2767.5878 4234.1221) (2773.9084 4233.2519)
      (2778.6412 4232.6718) (2780.7481 4231.6031) (2780.0153 4229.3588) (2777.084 4225.6031) (2773.2214 4220.5344)
      (2769.9389 4214.9008) (2768.4733 4209.8168) (2769.4962 4206.3969) (2772.916 4205.374) (2778.0 4206.8397)
      (2783.6336 4210.1221) (2788.7023 4213.9695) (2792.458 4216.9008) (2794.7023 4217.6336) (2795.771 4215.542)
      (2796.3664 4210.8092) (2797.2214 4204.4885) (2798.8855 4198.1832) (2801.4351 4193.5573) (2804.5802 4191.8626)
      (2807.7252 4193.5573) (2810.2748 4198.1832) (2811.9389 4204.4885) (2812.7939 4210.8092) (2813.3893 4215.542)
      (2814.458 4217.6336) (2816.7023 4216.9008) (2820.458 4213.9695) (2825.5267 4210.1221) (2831.1603 4206.8397)
      (2836.2443 4205.374) (2839.6641 4206.3969) (2840.687 4209.8168) (2839.2214 4214.9008) (2835.9389 4220.5344)
      (2832.0763 4225.6031) (2829.145 4229.3588) (2828.4122 4231.6031) (2830.5191 4232.6718) (2835.2519 4233.2519)
      (2841.5725 4234.1221) (2847.8779 4235.7863) (2852.5038 4238.3359) (2854.1985 4241.4809) (2852.5038 4244.626)
      (2847.8779 4247.1756) (2841.5725 4248.8397) (2835.2519 4249.6947) (2830.5191 4250.2901) (2828.4122 4251.3588)
      (2829.145 4253.6031) (2832.0763 4257.3588) (2835.9389 4262.4275) (2839.2214 4268.0611) (2840.687 4273.145)
      (2839.6641 4276.5649) (2836.2443 4277.5878) (2831.1603 4276.1221) (2825.5267 4272.8397) (2820.458 4268.9771)
      (2816.7023 4266.0458) (2814.458 4265.313) (2813.3893 4267.4198) (2812.7939 4272.1527) (2811.9389 4278.458)
      (2810.2748 4284.7634) (2807.7252 4289.4046) (2804.5802 4291.0992) (2801.4351 4289.4046) (2798.8855 4284.7634)
      (2797.2214 4278.458) (2796.3664 4272.1527) (2795.771 4267.4198) (2794.7023 4265.313) (2792.458 4266.0458)
      (2788.7023 4268.9771) (2783.6336 4272.8397) (2778.0 4276.1221) (2772.916 4277.5878) (2769.4962 4276.5649)
      (2768.4733 4273.145) (2769.9389 4268.0611) (2773.2214 4262.4275) (2777.084 4257.3588) (2780.0153 4253.6031)
      (2780.7481 4251.3588) (2778.6412 4250.2901) (2773.9084 4249.6947) (2767.5878 4248.8397) (2761.2824 4247.1756)
      (2756.6565 4244.626)
    ))
    ; P2388 -- see feature_dimensions_mm.csv
    ("06_ORNAMENT" 1 (
      (2754.9618 3930.0305) (2756.6565 3926.8855) (2761.2824 3924.3359) (2767.5878 3922.6718) (2773.9084 3921.8015)
      (2778.6412 3921.2214) (2780.7481 3920.1527) (2780.0153 3917.9084) (2777.084 3914.1527) (2773.2214 3909.084)
      (2769.9389 3903.4504) (2768.4733 3898.3664) (2769.4962 3894.9466) (2772.916 3893.9237) (2778.0 3895.3893)
      (2783.6336 3898.6718) (2788.7023 3902.5191) (2792.458 3905.4504) (2794.7023 3906.1832) (2795.771 3904.0916)
      (2796.3664 3899.3588) (2797.2214 3893.0382) (2798.8855 3886.7328) (2801.4351 3882.1069) (2804.5802 3880.4122)
      (2807.7252 3882.1069) (2810.2748 3886.7328) (2811.9389 3893.0382) (2812.7939 3899.3588) (2813.3893 3904.0916)
      (2814.458 3906.1832) (2816.7023 3905.4504) (2820.458 3902.5191) (2825.5267 3898.6718) (2831.1603 3895.3893)
      (2836.2443 3893.9237) (2839.6641 3894.9466) (2840.687 3898.3664) (2839.2214 3903.4504) (2835.9389 3909.084)
      (2832.0763 3914.1527) (2829.145 3917.9084) (2828.4122 3920.1527) (2830.5191 3921.2214) (2835.2519 3921.8015)
      (2841.5725 3922.6718) (2847.8779 3924.3359) (2852.5038 3926.8855) (2854.1985 3930.0305) (2852.5038 3933.1756)
      (2847.8779 3935.7252) (2841.5725 3937.3893) (2835.2519 3938.2443) (2830.5191 3938.8397) (2828.4122 3939.9084)
      (2829.145 3942.1527) (2832.0763 3945.9084) (2835.9389 3950.9771) (2839.2214 3956.6107) (2840.687 3961.6947)
      (2839.6641 3965.1145) (2836.2443 3966.1374) (2831.1603 3964.6718) (2825.5267 3961.3893) (2820.458 3957.5267)
      (2816.7023 3954.5954) (2814.458 3953.8626) (2813.3893 3955.9695) (2812.7939 3960.7023) (2811.9389 3967.0076)
      (2810.2748 3973.313) (2807.7252 3977.9542) (2804.5802 3979.6489) (2801.4351 3977.9542) (2798.8855 3973.313)
      (2797.2214 3967.0076) (2796.3664 3960.7023) (2795.771 3955.9695) (2794.7023 3953.8626) (2792.458 3954.5954)
      (2788.7023 3957.5267) (2783.6336 3961.3893) (2778.0 3964.6718) (2772.916 3966.1374) (2769.4962 3965.1145)
      (2768.4733 3961.6947) (2769.9389 3956.6107) (2773.2214 3950.9771) (2777.084 3945.9084) (2780.0153 3942.1527)
      (2780.7481 3939.9084) (2778.6412 3938.8397) (2773.9084 3938.2443) (2767.5878 3937.3893) (2761.2824 3935.7252)
      (2756.6565 3933.1756)
    ))
    ; P2389 -- see feature_dimensions_mm.csv
    ("06_ORNAMENT" 1 (
      (2786.2595 5253.6947) (2804.5802 5233.084) (2822.9008 5253.6947) (2804.5802 5274.3053)
    ))
    ; P2390 -- see feature_dimensions_mm.csv
    ("06_ORNAMENT" 1 (
      (2786.2595 4942.2443) (2804.5802 4921.6336) (2822.9008 4942.2443) (2804.5802 4962.855)
    ))
    ; P2391 -- see feature_dimensions_mm.csv
    ("06_ORNAMENT" 1 (
      (2786.2595 4630.7939) (2804.5802 4610.1832) (2822.9008 4630.7939) (2804.5802 4651.4046)
    ))
    ; P2392 -- see feature_dimensions_mm.csv
    ("06_ORNAMENT" 1 (
      (2786.2595 4319.3435) (2804.5802 4298.7328) (2822.9008 4319.3435) (2804.5802 4339.9542)
    ))
    ; P2393 -- see feature_dimensions_mm.csv
    ("06_ORNAMENT" 1 (
      (2786.2595 4007.8931) (2804.5802 3987.2824) (2822.9008 4007.8931) (2804.5802 4028.5038)
    ))
    ; P2394 -- see feature_dimensions_mm.csv
    ("06_ORNAMENT" 1 (
      (2792.6718 5487.2824) (2793.5725 5482.7176) (2796.1527 5478.855) (2800.0305 5476.2748) (2804.5802 5475.374)
      (2809.1298 5476.2748) (2813.0076 5478.855) (2815.5878 5482.7176) (2816.4885 5487.2824) (2815.5878 5491.8321)
      (2813.0076 5495.6947) (2809.1298 5498.2748) (2804.5802 5499.1908) (2800.0305 5498.2748) (2796.1527 5495.6947)
      (2793.5725 5491.8321)
    ))
    ; P2395 -- see feature_dimensions_mm.csv
    ("06_ORNAMENT" 1 (
      (2792.6718 5175.8321) (2793.5725 5171.2672) (2796.1527 5167.4046) (2800.0305 5164.8244) (2804.5802 5163.9237)
      (2809.1298 5164.8244) (2813.0076 5167.4046) (2815.5878 5171.2672) (2816.4885 5175.8321) (2815.5878 5180.3817)
      (2813.0076 5184.2443) (2809.1298 5186.8244) (2804.5802 5187.7405) (2800.0305 5186.8244) (2796.1527 5184.2443)
      (2793.5725 5180.3817)
    ))
    ; P2396 -- see feature_dimensions_mm.csv
    ("06_ORNAMENT" 1 (
      (2792.6718 4864.3817) (2793.5725 4859.8168) (2796.1527 4855.9542) (2800.0305 4853.374) (2804.5802 4852.4733)
      (2809.1298 4853.374) (2813.0076 4855.9542) (2815.5878 4859.8168) (2816.4885 4864.3817) (2815.5878 4868.9313)
      (2813.0076 4872.7939) (2809.1298 4875.374) (2804.5802 4876.2901) (2800.0305 4875.374) (2796.1527 4872.7939)
      (2793.5725 4868.9313)
    ))
    ; P2397 -- see feature_dimensions_mm.csv
    ("06_ORNAMENT" 1 (
      (2792.6718 4552.9313) (2793.5725 4548.3664) (2796.1527 4544.5038) (2800.0305 4541.9237) (2804.5802 4541.0229)
      (2809.1298 4541.9237) (2813.0076 4544.5038) (2815.5878 4548.3664) (2816.4885 4552.9313) (2815.5878 4557.4809)
      (2813.0076 4561.3435) (2809.1298 4563.9237) (2804.5802 4564.8397) (2800.0305 4563.9237) (2796.1527 4561.3435)
      (2793.5725 4557.4809)
    ))
    ; P2398 -- see feature_dimensions_mm.csv
    ("06_ORNAMENT" 1 (
      (2792.6718 4241.4809) (2793.5725 4236.916) (2796.1527 4233.0534) (2800.0305 4230.4733) (2804.5802 4229.5725)
      (2809.1298 4230.4733) (2813.0076 4233.0534) (2815.5878 4236.916) (2816.4885 4241.4809) (2815.5878 4246.0305)
      (2813.0076 4249.8931) (2809.1298 4252.4733) (2804.5802 4253.3893) (2800.0305 4252.4733) (2796.1527 4249.8931)
      (2793.5725 4246.0305)
    ))
    ; P2399 -- see feature_dimensions_mm.csv
    ("06_ORNAMENT" 1 (
      (2792.6718 3930.0305) (2793.5725 3925.4656) (2796.1527 3921.6031) (2800.0305 3919.0229) (2804.5802 3918.1221)
      (2809.1298 3919.0229) (2813.0076 3921.6031) (2815.5878 3925.4656) (2816.4885 3930.0305) (2815.5878 3934.5802)
      (2813.0076 3938.4427) (2809.1298 3941.0229) (2804.5802 3941.9389) (2800.0305 3941.0229) (2796.1527 3938.4427)
      (2793.5725 3934.5802)
    ))
    ; P2400 -- see feature_dimensions_mm.csv
    ("06_ORNAMENT" 1 (
      (2832.8244 5331.5573) (2834.5191 5328.4122) (2839.145 5325.8626) (2845.4504 5324.1985) (2851.771 5323.3282)
      (2856.5038 5322.7481) (2858.6107 5321.6794) (2857.8779 5319.4351) (2854.9466 5315.6794) (2851.084 5310.6107)
      (2847.8015 5304.9771) (2846.3359 5299.8931) (2847.3588 5296.4733) (2850.7786 5295.4504) (2855.8626 5296.916)
      (2861.4962 5300.1985) (2866.5649 5304.0458) (2870.3206 5306.9771) (2872.5649 5307.7099) (2873.6336 5305.6183)
      (2874.229 5300.8855) (2875.084 5294.5649) (2876.7481 5288.2595) (2879.2977 5283.6336) (2882.4427 5281.9389)
      (2885.5878 5283.6336) (2888.1374 5288.2595) (2889.8015 5294.5649) (2890.6565 5300.8855) (2891.2519 5305.6183)
      (2892.3206 5307.7099) (2894.5649 5306.9771) (2898.3206 5304.0458) (2903.3893 5300.1985) (2909.0229 5296.916)
      (2914.1069 5295.4504) (2917.5267 5296.4733) (2918.5496 5299.8931) (2917.084 5304.9771) (2913.8015 5310.6107)
      (2909.9389 5315.6794) (2907.0076 5319.4351) (2906.2748 5321.6794) (2908.3817 5322.7481) (2913.1145 5323.3282)
      (2919.4351 5324.1985) (2925.7405 5325.8626) (2930.3664 5328.4122) (2931.2977 5330.1374) (2931.2977 5332.9618)
      (2930.3664 5334.7023) (2925.7405 5337.2519) (2919.4351 5338.916) (2913.1145 5339.771) (2908.3817 5340.3664)
      (2906.2748 5341.4351) (2907.0076 5343.6794) (2909.9389 5347.4351) (2913.8015 5352.5038) (2917.084 5358.1374)
      (2918.5496 5363.2214) (2917.5267 5366.6412) (2914.1069 5367.6641) (2909.0229 5366.1985) (2903.3893 5362.916)
      (2898.3206 5359.0534) (2894.5649 5356.1221) (2892.3206 5355.3893) (2891.2519 5357.4962) (2890.6565 5362.229)
      (2889.8015 5368.5344) (2888.1374 5374.8397) (2885.5878 5379.4809) (2882.4427 5381.1756) (2879.2977 5379.4809)
      (2876.7481 5374.8397) (2875.084 5368.5344) (2874.229 5362.229) (2873.6336 5357.4962) (2872.5649 5355.3893)
      (2870.3206 5356.1221) (2866.5649 5359.0534) (2861.4962 5362.916) (2855.8626 5366.1985) (2850.7786 5367.6641)
      (2847.3588 5366.6412) (2846.3359 5363.2214) (2847.8015 5358.1374) (2851.084 5352.5038) (2854.9466 5347.4351)
      (2857.8779 5343.6794) (2858.6107 5341.4351) (2856.5038 5340.3664) (2851.771 5339.771) (2845.4504 5338.916)
      (2839.145 5337.2519) (2834.5191 5334.7023)
    ))
    ; P2401 -- see feature_dimensions_mm.csv
    ("06_ORNAMENT" 1 (
      (2832.8244 5020.1069) (2834.5191 5016.9618) (2839.145 5014.4122) (2845.4504 5012.7481) (2851.771 5011.8779)
      (2856.5038 5011.2977) (2858.6107 5010.229) (2857.8779 5007.9847) (2854.9466 5004.229) (2851.084 4999.1603)
      (2847.8015 4993.5267) (2846.3359 4988.4427) (2847.3588 4985.0229) (2850.7786 4984.0) (2855.8626 4985.4656)
      (2861.4962 4988.7481) (2866.5649 4992.5954) (2870.3206 4995.5267) (2872.5649 4996.2595) (2873.6336 4994.1679)
      (2874.229 4989.4351) (2875.084 4983.1145) (2876.7481 4976.8092) (2879.2977 4972.1832) (2882.4427 4970.4885)
      (2885.5878 4972.1832) (2888.1374 4976.8092) (2889.8015 4983.1145) (2890.6565 4989.4351) (2891.2519 4994.1679)
      (2892.3206 4996.2595) (2894.5649 4995.5267) (2898.3206 4992.5954) (2903.3893 4988.7481) (2909.0229 4985.4656)
      (2914.1069 4984.0) (2917.5267 4985.0229) (2918.5496 4988.4427) (2917.084 4993.5267) (2913.8015 4999.1603)
      (2909.9389 5004.229) (2907.0076 5007.9847) (2906.2748 5010.229) (2908.3817 5011.2977) (2913.1145 5011.8779)
      (2919.4351 5012.7481) (2925.7405 5014.4122) (2930.3664 5016.9618) (2931.2977 5018.687) (2931.2977 5021.5115)
      (2930.3664 5023.2519) (2925.7405 5025.8015) (2919.4351 5027.4656) (2913.1145 5028.3206) (2908.3817 5028.916)
      (2906.2748 5029.9847) (2907.0076 5032.229) (2909.9389 5035.9847) (2913.8015 5041.0534) (2917.084 5046.687)
      (2918.5496 5051.771) (2917.5267 5055.1908) (2914.1069 5056.2137) (2909.0229 5054.7481) (2903.3893 5051.4656)
      (2898.3206 5047.6031) (2894.5649 5044.6718) (2892.3206 5043.9389) (2891.2519 5046.0458) (2890.6565 5050.7786)
      (2889.8015 5057.084) (2888.1374 5063.3893) (2885.5878 5068.0305) (2882.4427 5069.7252) (2879.2977 5068.0305)
      (2876.7481 5063.3893) (2875.084 5057.084) (2874.229 5050.7786) (2873.6336 5046.0458) (2872.5649 5043.9389)
      (2870.3206 5044.6718) (2866.5649 5047.6031) (2861.4962 5051.4656) (2855.8626 5054.7481) (2850.7786 5056.2137)
      (2847.3588 5055.1908) (2846.3359 5051.771) (2847.8015 5046.687) (2851.084 5041.0534) (2854.9466 5035.9847)
      (2857.8779 5032.229) (2858.6107 5029.9847) (2856.5038 5028.916) (2851.771 5028.3206) (2845.4504 5027.4656)
      (2839.145 5025.8015) (2834.5191 5023.2519)
    ))
    ; P2402 -- see feature_dimensions_mm.csv
    ("06_ORNAMENT" 1 (
      (2832.8244 4708.6565) (2834.5191 4705.5115) (2839.145 4702.9618) (2845.4504 4701.2977) (2851.771 4700.4275)
      (2856.5038 4699.8473) (2858.6107 4698.7786) (2857.8779 4696.5344) (2854.9466 4692.7786) (2851.084 4687.7099)
      (2847.8015 4682.0763) (2846.3359 4676.9924) (2847.3588 4673.5725) (2850.7786 4672.5496) (2855.8626 4674.0153)
      (2861.4962 4677.2977) (2866.5649 4681.145) (2870.3206 4684.0763) (2872.5649 4684.8092) (2873.6336 4682.7176)
      (2874.229 4677.9847) (2875.084 4671.6641) (2876.7481 4665.3588) (2879.2977 4660.7328) (2882.4427 4659.0382)
      (2885.5878 4660.7328) (2888.1374 4665.3588) (2889.8015 4671.6641) (2890.6565 4677.9847) (2891.2519 4682.7176)
      (2892.3206 4684.8092) (2894.5649 4684.0763) (2898.3206 4681.145) (2903.3893 4677.2977) (2909.0229 4674.0153)
      (2914.1069 4672.5496) (2917.5267 4673.5725) (2918.5496 4676.9924) (2917.084 4682.0763) (2913.8015 4687.7099)
      (2909.9389 4692.7786) (2907.0076 4696.5344) (2906.2748 4698.7786) (2908.3817 4699.8473) (2913.1145 4700.4275)
      (2919.4351 4701.2977) (2925.7405 4702.9618) (2930.3664 4705.5115) (2931.2977 4707.2366) (2931.2977 4710.0611)
      (2930.3664 4711.8015) (2925.7405 4714.3511) (2919.4351 4716.0153) (2913.1145 4716.8702) (2908.3817 4717.4656)
      (2906.2748 4718.5344) (2907.0076 4720.7786) (2909.9389 4724.5344) (2913.8015 4729.6031) (2917.084 4735.2366)
      (2918.5496 4740.3206) (2917.5267 4743.7405) (2914.1069 4744.7634) (2909.0229 4743.2977) (2903.3893 4740.0153)
      (2898.3206 4736.1527) (2894.5649 4733.2214) (2892.3206 4732.4885) (2891.2519 4734.5954) (2890.6565 4739.3282)
      (2889.8015 4745.6336) (2888.1374 4751.9389) (2885.5878 4756.5802) (2882.4427 4758.2748) (2879.2977 4756.5802)
      (2876.7481 4751.9389) (2875.084 4745.6336) (2874.229 4739.3282) (2873.6336 4734.5954) (2872.5649 4732.4885)
      (2870.3206 4733.2214) (2866.5649 4736.1527) (2861.4962 4740.0153) (2855.8626 4743.2977) (2850.7786 4744.7634)
      (2847.3588 4743.7405) (2846.3359 4740.3206) (2847.8015 4735.2366) (2851.084 4729.6031) (2854.9466 4724.5344)
      (2857.8779 4720.7786) (2858.6107 4718.5344) (2856.5038 4717.4656) (2851.771 4716.8702) (2845.4504 4716.0153)
      (2839.145 4714.3511) (2834.5191 4711.8015)
    ))
    ; P2403 -- see feature_dimensions_mm.csv
    ("06_ORNAMENT" 1 (
      (2832.8244 4085.7557) (2834.5191 4082.6107) (2839.145 4080.0611) (2845.4504 4078.3969) (2851.771 4077.5267)
      (2856.5038 4076.9466) (2858.6107 4075.8779) (2857.8779 4073.6336) (2854.9466 4069.8779) (2851.084 4064.8092)
      (2847.8015 4059.1756) (2846.3359 4054.0916) (2847.3588 4050.6718) (2850.7786 4049.6489) (2855.8626 4051.1145)
      (2861.4962 4054.3969) (2866.5649 4058.2595) (2870.3206 4061.1756) (2872.5649 4061.9084) (2873.6336 4059.8168)
      (2874.229 4055.084) (2875.084 4048.7634) (2876.7481 4042.458) (2879.2977 4037.8321) (2882.4427 4036.1374)
      (2885.5878 4037.8321) (2888.1374 4042.458) (2889.8015 4048.7634) (2890.6565 4055.084) (2891.2519 4059.8168)
      (2892.3206 4061.9084) (2894.5649 4061.1756) (2898.3206 4058.2595) (2903.3893 4054.3969) (2909.0229 4051.1145)
      (2914.1069 4049.6489) (2917.5267 4050.6718) (2918.5496 4054.0916) (2917.084 4059.1756) (2913.8015 4064.8092)
      (2909.9389 4069.8779) (2907.0076 4073.6336) (2906.2748 4075.8779) (2908.3817 4076.9466) (2913.1145 4077.5267)
      (2919.4351 4078.3969) (2925.7405 4080.0611) (2930.3664 4082.6107) (2931.2977 4084.3359) (2931.2977 4087.1603)
      (2930.3664 4088.9008) (2925.7405 4091.4504) (2919.4351 4093.1145) (2913.1145 4093.9695) (2908.3817 4094.5649)
      (2906.2748 4095.6336) (2907.0076 4097.8779) (2909.9389 4101.6336) (2913.8015 4106.7023) (2917.084 4112.3359)
      (2918.5496 4117.4198) (2917.5267 4120.8397) (2914.1069 4121.8626) (2909.0229 4120.3969) (2903.3893 4117.1145)
      (2898.3206 4113.2519) (2894.5649 4110.3206) (2892.3206 4109.5878) (2891.2519 4111.6947) (2890.6565 4116.4275)
      (2889.8015 4122.7328) (2888.1374 4129.0382) (2885.5878 4133.6794) (2882.4427 4135.374) (2879.2977 4133.6794)
      (2876.7481 4129.0382) (2875.084 4122.7328) (2874.229 4116.4275) (2873.6336 4111.6947) (2872.5649 4109.5878)
      (2870.3206 4110.3206) (2866.5649 4113.2519) (2861.4962 4117.1145) (2855.8626 4120.3969) (2850.7786 4121.8626)
      (2847.3588 4120.8397) (2846.3359 4117.4198) (2847.8015 4112.3359) (2851.084 4106.7023) (2854.9466 4101.6336)
      (2857.8779 4097.8779) (2858.6107 4095.6336) (2856.5038 4094.5649) (2851.771 4093.9695) (2845.4504 4093.1145)
      (2839.145 4091.4504) (2834.5191 4088.9008)
    ))
    ; P2404 -- see feature_dimensions_mm.csv
    ("06_ORNAMENT" 1 (
      (2864.1221 5409.4198) (2882.4427 5388.8092) (2900.7634 5409.4198) (2882.4427 5430.0305)
    ))
    ; P2405 -- see feature_dimensions_mm.csv
    ("06_ORNAMENT" 1 (
      (2864.1221 5097.9695) (2882.4427 5077.3588) (2900.7634 5097.9695) (2882.4427 5118.5802)
    ))
    ; P2406 -- see feature_dimensions_mm.csv
    ("06_ORNAMENT" 1 (
      (2864.1221 4786.5191) (2882.4427 4765.9084) (2900.7634 4786.5191) (2882.4427 4807.1298)
    ))
    ; P2407 -- see feature_dimensions_mm.csv
    ("06_ORNAMENT" 1 (
      (2864.1221 4163.6183) (2882.4427 4143.0076) (2900.7634 4163.6183) (2882.4427 4184.229)
    ))
    ; P2408 -- see feature_dimensions_mm.csv
    ("06_ORNAMENT" 1 (
      (2864.1221 3852.1679) (2882.0 3832.0611) (2882.8855 3832.0611) (2900.7634 3852.1679) (2882.4427 3872.7786)
    ))
    ; P2409 -- see feature_dimensions_mm.csv
    ("06_ORNAMENT" 1 (
      (2870.5344 5331.5573) (2871.4351 5326.9924) (2874.0153 5323.1298) (2877.8931 5320.5496) (2882.4427 5319.6489)
      (2886.9924 5320.5496) (2890.8702 5323.1298) (2893.4504 5326.9924) (2894.3511 5331.5573) (2893.4504 5336.1069)
      (2890.8702 5339.9695) (2886.9924 5342.5496) (2882.4427 5343.4656) (2877.8931 5342.5496) (2874.0153 5339.9695)
      (2871.4351 5336.1069)
    ))
    ; P2410 -- see feature_dimensions_mm.csv
    ("06_ORNAMENT" 1 (
      (2870.5344 5020.1069) (2871.4351 5015.542) (2874.0153 5011.6794) (2877.8931 5009.0992) (2882.4427 5008.1985)
      (2886.9924 5009.0992) (2890.8702 5011.6794) (2893.4504 5015.542) (2894.3511 5020.1069) (2893.4504 5024.6565)
      (2890.8702 5028.5191) (2886.9924 5031.0992) (2882.4427 5032.0153) (2877.8931 5031.0992) (2874.0153 5028.5191)
      (2871.4351 5024.6565)
    ))
    ; P2411 -- see feature_dimensions_mm.csv
    ("06_ORNAMENT" 1 (
      (2870.5344 4708.6565) (2871.4351 4704.0916) (2874.0153 4700.229) (2877.8931 4697.6489) (2882.4427 4696.7481)
      (2886.9924 4697.6489) (2890.8702 4700.229) (2893.4504 4704.0916) (2894.3511 4708.6565) (2893.4504 4713.2061)
      (2890.8702 4717.0687) (2886.9924 4719.6489) (2882.4427 4720.5649) (2877.8931 4719.6489) (2874.0153 4717.0687)
      (2871.4351 4713.2061)
    ))
    ; P2412 -- see feature_dimensions_mm.csv
    ("06_ORNAMENT" 1 (
      (2870.5344 4397.2061) (2871.4351 4392.6412) (2874.0153 4388.7786) (2877.8931 4386.1985) (2882.4427 4385.2977)
      (2886.9924 4386.1985) (2890.8702 4388.7786) (2893.4504 4392.6412) (2894.3511 4397.2061) (2893.4504 4401.7557)
      (2890.8702 4405.6183) (2886.9924 4408.1985) (2882.4427 4409.1145) (2877.8931 4408.1985) (2874.0153 4405.6183)
      (2871.4351 4401.7557)
    ))
    ; P2413 -- see feature_dimensions_mm.csv
    ("06_ORNAMENT" 1 (
      (2870.5344 4085.7557) (2871.4351 4081.1908) (2874.0153 4077.3282) (2877.8931 4074.7481) (2882.4427 4073.8473)
      (2886.9924 4074.7481) (2890.8702 4077.3282) (2893.4504 4081.1908) (2894.3511 4085.7557) (2893.4504 4090.3053)
      (2890.8702 4094.1679) (2886.9924 4096.7481) (2882.4427 4097.6641) (2877.8931 4096.7481) (2874.0153 4094.1679)
      (2871.4351 4090.3053)
    ))
    ; P2414 -- see feature_dimensions_mm.csv
    ("06_ORNAMENT" 1 (
      (2910.687 5487.2824) (2912.3817 5484.1374) (2917.0076 5481.5878) (2923.313 5479.9237) (2929.6336 5479.0534)
      (2931.2977 5478.855) (2931.2977 5495.7099) (2929.6336 5495.4962) (2923.313 5494.6412) (2917.0076 5492.9771)
      (2912.3817 5490.4275)
    ))
    ; P2415 -- see feature_dimensions_mm.csv
    ("06_ORNAMENT" 1 (
      (2910.687 5175.8321) (2912.3817 5172.687) (2917.0076 5170.1374) (2923.313 5168.4733) (2929.6336 5167.6031)
      (2931.2977 5167.4046) (2931.2977 5184.2595) (2929.6336 5184.0458) (2923.313 5183.1908) (2917.0076 5181.5267)
      (2912.3817 5178.9771)
    ))
    ; P2416 -- see feature_dimensions_mm.csv
    ("06_ORNAMENT" 1 (
      (2910.687 4864.3817) (2912.3817 4861.2366) (2917.0076 4858.687) (2923.313 4857.0229) (2929.6336 4856.1527)
      (2931.2977 4855.9542) (2931.2977 4872.8092) (2929.6336 4872.5954) (2923.313 4871.7405) (2917.0076 4870.0763)
      (2912.3817 4867.5267)
    ))
    ; P2417 -- see feature_dimensions_mm.csv
    ("06_ORNAMENT" 1 (
      (2910.687 4552.9313) (2912.3817 4549.7863) (2917.0076 4547.2366) (2923.313 4545.5725) (2929.6336 4544.7023)
      (2931.2977 4544.5038) (2931.2977 4561.3588) (2929.6336 4561.145) (2923.313 4560.2901) (2917.0076 4558.626)
      (2912.3817 4556.0763)
    ))
    ; P2418 -- see feature_dimensions_mm.csv
    ("06_ORNAMENT" 1 (
      (2910.687 4241.4809) (2912.3817 4238.3359) (2917.0076 4235.7863) (2923.313 4234.1221) (2929.6336 4233.2519)
      (2931.2977 4233.0534) (2931.2977 4249.9084) (2929.6336 4249.6947) (2923.313 4248.8397) (2917.0076 4247.1756)
      (2912.3817 4244.626)
    ))
    ; P2419 -- see feature_dimensions_mm.csv
    ("06_ORNAMENT" 1 (
      (2910.687 3930.0305) (2912.3817 3926.8855) (2917.0076 3924.3359) (2923.313 3922.6718) (2929.6336 3921.8015)
      (2931.2977 3921.6031) (2931.2977 3938.458) (2929.6336 3938.2443) (2923.313 3937.3893) (2917.0076 3935.7252)
      (2912.3817 3933.1756)
    ))
    ; P2420 -- see feature_dimensions_mm.csv
    ("06_ORNAMENT" 1 (
      (2924.1985 5518.9466) (2925.6641 5513.8626) (2928.9466 5508.229) (2931.2977 5505.145) (2931.2977 5522.626)
      (2928.6412 5523.3893) (2925.2214 5522.3664)
    ))
    ; P2421 -- see feature_dimensions_mm.csv
    ("06_ORNAMENT" 1 (
      (2924.1985 5455.6183) (2925.2214 5452.1985) (2928.6412 5451.1756) (2931.2977 5451.9389) (2931.2977 5469.4198)
      (2928.9466 5466.3359) (2925.6641 5460.7023)
    ))
    ; P2422 -- see feature_dimensions_mm.csv
    ("06_ORNAMENT" 1 (
      (2924.1985 5207.4962) (2925.6641 5202.4122) (2928.9466 5196.7786) (2931.2977 5193.6947) (2931.2977 5211.1756)
      (2928.6412 5211.9389) (2925.2214 5210.916)
    ))
    ; P2423 -- see feature_dimensions_mm.csv
    ("06_ORNAMENT" 1 (
      (2924.1985 5144.1679) (2925.2214 5140.7481) (2928.6412 5139.7252) (2931.2977 5140.4885) (2931.2977 5157.9695)
      (2928.9466 5154.8855) (2925.6641 5149.2519)
    ))
    ; P2424 -- see feature_dimensions_mm.csv
    ("06_ORNAMENT" 1 (
      (2924.1985 4896.0458) (2925.6641 4890.9618) (2928.9466 4885.3282) (2931.2977 4882.2443) (2931.2977 4899.7252)
      (2928.6412 4900.4885) (2925.2214 4899.4656)
    ))
    ; P2425 -- see feature_dimensions_mm.csv
    ("06_ORNAMENT" 1 (
      (2924.1985 4832.7176) (2925.2214 4829.2977) (2928.6412 4828.2748) (2931.2977 4829.0382) (2931.2977 4846.5191)
      (2928.9466 4843.4351) (2925.6641 4837.8015)
    ))
    ; P2426 -- see feature_dimensions_mm.csv
    ("06_ORNAMENT" 1 (
      (2924.1985 4584.5954) (2925.6641 4579.5115) (2928.9466 4573.8779) (2931.2977 4570.7939) (2931.2977 4588.2748)
      (2928.6412 4589.0382) (2925.2214 4588.0153)
    ))
    ; P2427 -- see feature_dimensions_mm.csv
    ("06_ORNAMENT" 1 (
      (2924.1985 4521.2672) (2925.2214 4517.8473) (2928.6412 4516.8244) (2931.2977 4517.5878) (2931.2977 4535.0687)
      (2928.9466 4531.9847) (2925.6641 4526.3511)
    ))
    ; P2428 -- see feature_dimensions_mm.csv
    ("06_ORNAMENT" 1 (
      (2924.1985 4273.145) (2925.6641 4268.0611) (2928.9466 4262.4275) (2931.2977 4259.3435) (2931.2977 4276.8244)
      (2928.6412 4277.5878) (2925.2214 4276.5649)
    ))
    ; P2429 -- see feature_dimensions_mm.csv
    ("06_ORNAMENT" 1 (
      (2924.1985 4209.8168) (2925.2214 4206.3969) (2928.6412 4205.374) (2931.2977 4206.1374) (2931.2977 4223.6183)
      (2928.9466 4220.5344) (2925.6641 4214.9008)
    ))
    ; P2430 -- see feature_dimensions_mm.csv
    ("06_ORNAMENT" 1 (
      (2924.1985 3961.6947) (2925.6641 3956.6107) (2928.9466 3950.9771) (2931.2977 3947.8931) (2931.2977 3965.374)
      (2928.6412 3966.1374) (2925.2214 3965.1145)
    ))
    ; P2431 -- see feature_dimensions_mm.csv
    ("06_ORNAMENT" 1 (
      (2924.1985 3898.3664) (2925.2214 3894.9466) (2928.6412 3893.9237) (2931.2977 3894.687) (2931.2977 3912.1679)
      (2928.9466 3909.084) (2925.6641 3903.4504)
    ))
    ; P2432 -- see feature_dimensions_mm.csv
    ("06_ORNAMENT" 1 (
      (2931.2977 6061.0687) (2933.542 6046.916) (2940.0458 6034.1527) (2950.1832 6024.0153) (2962.9466 6017.5115)
      (2977.0992 6015.2672) (2991.2519 6017.5115) (3004.0153 6024.0153) (3014.1527 6034.1527) (3020.6565 6046.916)
      (3022.9008 6061.0687) (3020.6565 6075.2214) (3014.1527 6087.9847) (3004.0153 6098.1221) (2991.2519 6104.626)
      (2977.0992 6106.8702) (2962.9466 6104.626) (2950.1832 6098.1221) (2940.0458 6087.9847) (2933.542 6075.2214)
    ))
    ; P2433 -- see feature_dimensions_mm.csv
    ("06_ORNAMENT" 1 (
      (3022.9008 5412.855) (3022.9008 5405.9847) (3038.1679 5388.8092) (3056.4885 5409.4198) (3038.1679 5430.0305)
    ))
    ; P2434 -- see feature_dimensions_mm.csv
    ("06_ORNAMENT" 1 (
      (3022.9008 5358.5802) (3022.9008 5304.5344) (3026.0458 5306.9771) (3028.2901 5307.7099) (3029.3588 5305.6183)
      (3029.9542 5300.8855) (3030.8092 5294.5649) (3032.4733 5288.2595) (3035.0229 5283.6336) (3038.1679 5281.9389)
      (3041.313 5283.6336) (3043.8626 5288.2595) (3045.5267 5294.5649) (3046.3817 5300.8855) (3046.9771 5305.6183)
      (3048.0458 5307.7099) (3050.2901 5306.9771) (3054.0458 5304.0458) (3059.1145 5300.1985) (3064.7481 5296.916)
      (3069.8321 5295.4504) (3073.2519 5296.4733) (3074.2748 5299.8931) (3072.8092 5304.9771) (3069.5267 5310.6107)
      (3065.6641 5315.6794) (3062.7328 5319.4351) (3062.0 5321.6794) (3064.1069 5322.7481) (3068.8397 5323.3282)
      (3075.1603 5324.1985) (3081.4656 5325.8626) (3086.0916 5328.4122) (3087.7863 5331.5573) (3086.0916 5334.7023)
      (3081.4656 5337.2519) (3075.1603 5338.916) (3068.8397 5339.771) (3064.1069 5340.3664) (3062.0 5341.4351)
      (3062.7328 5343.6794) (3065.6641 5347.4351) (3069.5267 5352.5038) (3072.8092 5358.1374) (3074.2748 5363.2214)
      (3073.2519 5366.6412) (3069.8321 5367.6641) (3064.7481 5366.1985) (3059.1145 5362.916) (3054.0458 5359.0534)
      (3050.2901 5356.1221) (3048.0458 5355.3893) (3046.9771 5357.4962) (3046.3817 5362.229) (3045.5267 5368.5344)
      (3043.8626 5374.8397) (3041.313 5379.4809) (3038.1679 5381.1756) (3035.0229 5379.4809) (3032.4733 5374.8397)
      (3030.8092 5368.5344) (3029.9542 5362.229) (3029.3588 5357.4962) (3028.2901 5355.3893) (3026.0458 5356.1221)
    ))
    ; P2435 -- see feature_dimensions_mm.csv
    ("06_ORNAMENT" 1 (
      (3022.9008 5101.4046) (3022.9008 5094.5344) (3038.1679 5077.3588) (3056.4885 5097.9695) (3038.1679 5118.5802)
    ))
    ; P2436 -- see feature_dimensions_mm.csv
    ("06_ORNAMENT" 1 (
      (3022.9008 5047.1298) (3022.9008 4993.084) (3026.0458 4995.5267) (3028.2901 4996.2595) (3029.3588 4994.1679)
      (3029.9542 4989.4351) (3030.8092 4983.1145) (3032.4733 4976.8092) (3035.0229 4972.1832) (3038.1679 4970.4885)
      (3041.313 4972.1832) (3043.8626 4976.8092) (3045.5267 4983.1145) (3046.3817 4989.4351) (3046.9771 4994.1679)
      (3048.0458 4996.2595) (3050.2901 4995.5267) (3054.0458 4992.5954) (3059.1145 4988.7481) (3064.7481 4985.4656)
      (3069.8321 4984.0) (3073.2519 4985.0229) (3074.2748 4988.4427) (3072.8092 4993.5267) (3069.5267 4999.1603)
      (3065.6641 5004.229) (3062.7328 5007.9847) (3062.0 5010.229) (3064.1069 5011.2977) (3068.8397 5011.8779)
      (3075.1603 5012.7481) (3081.4656 5014.4122) (3086.0916 5016.9618) (3087.7863 5020.1069) (3086.0916 5023.2519)
      (3081.4656 5025.8015) (3075.1603 5027.4656) (3068.8397 5028.3206) (3064.1069 5028.916) (3062.0 5029.9847)
      (3062.7328 5032.229) (3065.6641 5035.9847) (3069.5267 5041.0534) (3072.8092 5046.687) (3074.2748 5051.771)
      (3073.2519 5055.1908) (3069.8321 5056.2137) (3064.7481 5054.7481) (3059.1145 5051.4656) (3054.0458 5047.6031)
      (3050.2901 5044.6718) (3048.0458 5043.9389) (3046.9771 5046.0458) (3046.3817 5050.7786) (3045.5267 5057.084)
      (3043.8626 5063.3893) (3041.313 5068.0305) (3038.1679 5069.7252) (3035.0229 5068.0305) (3032.4733 5063.3893)
      (3030.8092 5057.084) (3029.9542 5050.7786) (3029.3588 5046.0458) (3028.2901 5043.9389) (3026.0458 5044.6718)
    ))
    ; P2437 -- see feature_dimensions_mm.csv
    ("06_ORNAMENT" 1 (
      (3022.9008 4789.9542) (3022.9008 4783.084) (3038.1679 4765.9084) (3056.4885 4786.5191) (3038.1679 4807.1298)
    ))
    ; P2438 -- see feature_dimensions_mm.csv
    ("06_ORNAMENT" 1 (
      (3022.9008 4735.6794) (3022.9008 4681.6336) (3026.0458 4684.0763) (3028.2901 4684.8092) (3029.3588 4682.7176)
      (3029.9542 4677.9847) (3030.8092 4671.6641) (3032.4733 4665.3588) (3035.0229 4660.7328) (3038.1679 4659.0382)
      (3041.313 4660.7328) (3043.8626 4665.3588) (3045.5267 4671.6641) (3046.3817 4677.9847) (3046.9771 4682.7176)
      (3048.0458 4684.8092) (3050.2901 4684.0763) (3054.0458 4681.145) (3059.1145 4677.2977) (3064.7481 4674.0153)
      (3069.8321 4672.5496) (3073.2519 4673.5725) (3074.2748 4676.9924) (3072.8092 4682.0763) (3069.5267 4687.7099)
      (3065.6641 4692.7786) (3062.7328 4696.5344) (3062.0 4698.7786) (3064.1069 4699.8473) (3068.8397 4700.4275)
      (3075.1603 4701.2977) (3081.4656 4702.9618) (3086.0916 4705.5115) (3087.7863 4708.6565) (3086.0916 4711.8015)
      (3081.4656 4714.3511) (3075.1603 4716.0153) (3068.8397 4716.8702) (3064.1069 4717.4656) (3062.0 4718.5344)
      (3062.7328 4720.7786) (3065.6641 4724.5344) (3069.5267 4729.6031) (3072.8092 4735.2366) (3074.2748 4740.3206)
      (3073.2519 4743.7405) (3069.8321 4744.7634) (3064.7481 4743.2977) (3059.1145 4740.0153) (3054.0458 4736.1527)
      (3050.2901 4733.2214) (3048.0458 4732.4885) (3046.9771 4734.5954) (3046.3817 4739.3282) (3045.5267 4745.6336)
      (3043.8626 4751.9389) (3041.313 4756.5802) (3038.1679 4758.2748) (3035.0229 4756.5802) (3032.4733 4751.9389)
      (3030.8092 4745.6336) (3029.9542 4739.3282) (3029.3588 4734.5954) (3028.2901 4732.4885) (3026.0458 4733.2214)
    ))
    ; P2439 -- see feature_dimensions_mm.csv
    ("06_ORNAMENT" 1 (
      (3022.9008 4167.0534) (3022.9008 4160.1832) (3038.1679 4143.0076) (3056.4885 4163.6183) (3038.1679 4184.229)
    ))
    ; P2440 -- see feature_dimensions_mm.csv
    ("06_ORNAMENT" 1 (
      (3022.9008 4112.7786) (3022.9008 4058.7328) (3026.0458 4061.1756) (3028.2901 4061.9084) (3029.3588 4059.8168)
      (3029.9542 4055.084) (3030.8092 4048.7634) (3032.4733 4042.458) (3035.0229 4037.8321) (3038.1679 4036.1374)
      (3041.313 4037.8321) (3043.8626 4042.458) (3045.5267 4048.7634) (3046.3817 4055.084) (3046.9771 4059.8168)
      (3048.0458 4061.9084) (3050.2901 4061.1756) (3054.0458 4058.2595) (3059.1145 4054.3969) (3064.7481 4051.1145)
      (3069.8321 4049.6489) (3073.2519 4050.6718) (3074.2748 4054.0916) (3072.8092 4059.1756) (3069.5267 4064.8092)
      (3065.6641 4069.8779) (3062.7328 4073.6336) (3062.0 4075.8779) (3064.1069 4076.9466) (3068.8397 4077.5267)
      (3075.1603 4078.3969) (3081.4656 4080.0611) (3086.0916 4082.6107) (3087.7863 4085.7557) (3086.0916 4088.9008)
      (3081.4656 4091.4504) (3075.1603 4093.1145) (3068.8397 4093.9695) (3064.1069 4094.5649) (3062.0 4095.6336)
      (3062.7328 4097.8779) (3065.6641 4101.6336) (3069.5267 4106.7023) (3072.8092 4112.3359) (3074.2748 4117.4198)
      (3073.2519 4120.8397) (3069.8321 4121.8626) (3064.7481 4120.3969) (3059.1145 4117.1145) (3054.0458 4113.2519)
      (3050.2901 4110.3206) (3048.0458 4109.5878) (3046.9771 4111.6947) (3046.3817 4116.4275) (3045.5267 4122.7328)
      (3043.8626 4129.0382) (3041.313 4133.6794) (3038.1679 4135.374) (3035.0229 4133.6794) (3032.4733 4129.0382)
      (3030.8092 4122.7328) (3029.9542 4116.4275) (3029.3588 4111.6947) (3028.2901 4109.5878) (3026.0458 4110.3206)
    ))
    ; P2441 -- see feature_dimensions_mm.csv
    ("06_ORNAMENT" 1 (
      (3026.2595 5331.5573) (3027.1603 5326.9924) (3029.7405 5323.1298) (3033.6183 5320.5496) (3038.1679 5319.6489)
      (3042.7176 5320.5496) (3046.5954 5323.1298) (3049.1756 5326.9924) (3050.0763 5331.5573) (3049.1756 5336.1069)
      (3046.5954 5339.9695) (3042.7176 5342.5496) (3038.1679 5343.4656) (3033.6183 5342.5496) (3029.7405 5339.9695)
      (3027.1603 5336.1069)
    ))
    ; P2442 -- see feature_dimensions_mm.csv
    ("06_ORNAMENT" 1 (
      (3026.2595 5020.1069) (3027.1603 5015.542) (3029.7405 5011.6794) (3033.6183 5009.0992) (3038.1679 5008.1985)
      (3042.7176 5009.0992) (3046.5954 5011.6794) (3049.1756 5015.542) (3050.0763 5020.1069) (3049.1756 5024.6565)
      (3046.5954 5028.5191) (3042.7176 5031.0992) (3038.1679 5032.0153) (3033.6183 5031.0992) (3029.7405 5028.5191)
      (3027.1603 5024.6565)
    ))
    ; P2443 -- see feature_dimensions_mm.csv
    ("06_ORNAMENT" 1 (
      (3026.2595 4708.6565) (3027.1603 4704.0916) (3029.7405 4700.229) (3033.6183 4697.6489) (3038.1679 4696.7481)
      (3042.7176 4697.6489) (3046.5954 4700.229) (3049.1756 4704.0916) (3050.0763 4708.6565) (3049.1756 4713.2061)
      (3046.5954 4717.0687) (3042.7176 4719.6489) (3038.1679 4720.5649) (3033.6183 4719.6489) (3029.7405 4717.0687)
      (3027.1603 4713.2061)
    ))
    ; P2444 -- see feature_dimensions_mm.csv
    ("06_ORNAMENT" 1 (
      (3026.2595 4397.2061) (3027.1603 4392.6412) (3029.7405 4388.7786) (3033.6183 4386.1985) (3038.1679 4385.2977)
      (3042.7176 4386.1985) (3046.5954 4388.7786) (3049.1756 4392.6412) (3050.0763 4397.2061) (3049.1756 4401.7557)
      (3046.5954 4405.6183) (3042.7176 4408.1985) (3038.1679 4409.1145) (3033.6183 4408.1985) (3029.7405 4405.6183)
      (3027.1603 4401.7557)
    ))
    ; P2445 -- see feature_dimensions_mm.csv
    ("06_ORNAMENT" 1 (
      (3026.2595 4085.7557) (3027.1603 4081.1908) (3029.7405 4077.3282) (3033.6183 4074.7481) (3038.1679 4073.8473)
      (3042.7176 4074.7481) (3046.5954 4077.3282) (3049.1756 4081.1908) (3050.0763 4085.7557) (3049.1756 4090.3053)
      (3046.5954 4094.1679) (3042.7176 4096.7481) (3038.1679 4097.6641) (3033.6183 4096.7481) (3029.7405 4094.1679)
      (3027.1603 4090.3053)
    ))
    ; P2446 -- see feature_dimensions_mm.csv
    ("06_ORNAMENT" 1 (
      (3066.4122 5487.2824) (3068.1069 5484.1374) (3072.7328 5481.5878) (3079.0382 5479.9237) (3085.3588 5479.0534)
      (3090.0916 5478.4733) (3092.1985 5477.4046) (3091.4656 5475.1603) (3088.5344 5471.4046) (3084.6718 5466.3359)
      (3081.3893 5460.7023) (3079.9237 5455.6183) (3080.9466 5452.1985) (3084.3664 5451.1756) (3089.4504 5452.6412)
      (3095.084 5455.9237) (3100.1527 5459.771) (3103.9084 5462.7023) (3106.1527 5463.4351) (3107.2214 5461.3435)
      (3107.8168 5456.6107) (3108.6718 5450.2901) (3110.3359 5443.9847) (3112.8855 5439.3588) (3116.0305 5437.6641)
      (3119.1756 5439.3588) (3121.7252 5443.9847) (3123.3893 5450.2901) (3124.2443 5456.6107) (3124.8397 5461.3435)
      (3125.9084 5463.4351) (3128.1527 5462.7023) (3131.9084 5459.771) (3136.9771 5455.9237) (3142.6107 5452.6412)
      (3147.6947 5451.1756) (3151.1145 5452.1985) (3152.1374 5455.6183) (3150.6718 5460.7023) (3147.3893 5466.3359)
      (3143.5267 5471.4046) (3140.5954 5475.1603) (3139.8626 5477.4046) (3141.9695 5478.4733) (3146.7023 5479.0534)
      (3153.0229 5479.9237) (3159.3282 5481.5878) (3163.9542 5484.1374) (3165.6489 5487.2824) (3163.9542 5490.4275)
      (3159.3282 5492.9771) (3153.0229 5494.6412) (3146.7023 5495.4962) (3141.9695 5496.0916) (3139.8626 5497.1603)
      (3140.5954 5499.4046) (3143.5267 5503.1603) (3147.3893 5508.229) (3150.6718 5513.8626) (3152.1374 5518.9466)
      (3151.1145 5522.3664) (3147.6947 5523.3893) (3142.6107 5521.9237) (3136.9771 5518.6412) (3131.9084 5514.7786)
      (3128.1527 5511.8473) (3125.9084 5511.1145) (3124.8397 5513.2214) (3124.2443 5517.9542) (3123.3893 5524.2595)
      (3121.7252 5530.5649) (3119.1756 5535.2061) (3116.0305 5536.9008) (3112.8855 5535.2061) (3110.3359 5530.5649)
      (3108.6718 5524.2595) (3107.8168 5517.9542) (3107.2214 5513.2214) (3106.1527 5511.1145) (3103.9084 5511.8473)
      (3100.1527 5514.7786) (3095.084 5518.6412) (3089.4504 5521.9237) (3084.3664 5523.3893) (3080.9466 5522.3664)
      (3079.9237 5518.9466) (3081.3893 5513.8626) (3084.6718 5508.229) (3088.5344 5503.1603) (3091.4656 5499.4046)
      (3092.1985 5497.1603) (3090.0916 5496.0916) (3085.3588 5495.4962) (3079.0382 5494.6412) (3072.7328 5492.9771)
      (3068.1069 5490.4275)
    ))
    ; P2447 -- see feature_dimensions_mm.csv
    ("06_ORNAMENT" 1 (
      (3066.4122 5175.8321) (3068.1069 5172.687) (3072.7328 5170.1374) (3079.0382 5168.4733) (3085.3588 5167.6031)
      (3090.0916 5167.0229) (3092.1985 5165.9542) (3091.4656 5163.7099) (3088.5344 5159.9542) (3084.6718 5154.8855)
      (3081.3893 5149.2519) (3079.9237 5144.1679) (3080.9466 5140.7481) (3084.3664 5139.7252) (3089.4504 5141.1908)
      (3095.084 5144.4733) (3100.1527 5148.3206) (3103.9084 5151.2519) (3106.1527 5151.9847) (3107.2214 5149.8931)
      (3107.8168 5145.1603) (3108.6718 5138.8397) (3110.3359 5132.5344) (3112.8855 5127.9084) (3116.0305 5126.2137)
      (3119.1756 5127.9084) (3121.7252 5132.5344) (3123.3893 5138.8397) (3124.2443 5145.1603) (3124.8397 5149.8931)
      (3125.9084 5151.9847) (3128.1527 5151.2519) (3131.9084 5148.3206) (3136.9771 5144.4733) (3142.6107 5141.1908)
      (3147.6947 5139.7252) (3151.1145 5140.7481) (3152.1374 5144.1679) (3150.6718 5149.2519) (3147.3893 5154.8855)
      (3143.5267 5159.9542) (3140.5954 5163.7099) (3139.8626 5165.9542) (3141.9695 5167.0229) (3146.7023 5167.6031)
      (3153.0229 5168.4733) (3159.3282 5170.1374) (3163.9542 5172.687) (3165.6489 5175.8321) (3163.9542 5178.9771)
      (3159.3282 5181.5267) (3153.0229 5183.1908) (3146.7023 5184.0458) (3141.9695 5184.6412) (3139.8626 5185.7099)
      (3140.5954 5187.9542) (3143.5267 5191.7099) (3147.3893 5196.7786) (3150.6718 5202.4122) (3152.1374 5207.4962)
      (3151.1145 5210.916) (3147.6947 5211.9389) (3142.6107 5210.4733) (3136.9771 5207.1908) (3131.9084 5203.3282)
      (3128.1527 5200.3969) (3125.9084 5199.6641) (3124.8397 5201.771) (3124.2443 5206.5038) (3123.3893 5212.8092)
      (3121.7252 5219.1145) (3119.1756 5223.7557) (3116.0305 5225.4504) (3112.8855 5223.7557) (3110.3359 5219.1145)
      (3108.6718 5212.8092) (3107.8168 5206.5038) (3107.2214 5201.771) (3106.1527 5199.6641) (3103.9084 5200.3969)
      (3100.1527 5203.3282) (3095.084 5207.1908) (3089.4504 5210.4733) (3084.3664 5211.9389) (3080.9466 5210.916)
      (3079.9237 5207.4962) (3081.3893 5202.4122) (3084.6718 5196.7786) (3088.5344 5191.7099) (3091.4656 5187.9542)
      (3092.1985 5185.7099) (3090.0916 5184.6412) (3085.3588 5184.0458) (3079.0382 5183.1908) (3072.7328 5181.5267)
      (3068.1069 5178.9771)
    ))
    ; P2448 -- see feature_dimensions_mm.csv
    ("06_ORNAMENT" 1 (
      (3066.4122 4864.3817) (3068.1069 4861.2366) (3072.7328 4858.687) (3079.0382 4857.0229) (3085.3588 4856.1527)
      (3090.0916 4855.5725) (3092.1985 4854.5038) (3091.4656 4852.2595) (3088.5344 4848.5038) (3084.6718 4843.4351)
      (3081.3893 4837.8015) (3079.9237 4832.7176) (3080.9466 4829.2977) (3084.3664 4828.2748) (3089.4504 4829.7405)
      (3095.084 4833.0229) (3100.1527 4836.8702) (3103.9084 4839.8015) (3106.1527 4840.5344) (3107.2214 4838.4427)
      (3107.8168 4833.7099) (3108.6718 4827.3893) (3110.3359 4821.084) (3112.8855 4816.458) (3116.0305 4814.7634)
      (3119.1756 4816.458) (3121.7252 4821.084) (3123.3893 4827.3893) (3124.2443 4833.7099) (3124.8397 4838.4427)
      (3125.9084 4840.5344) (3128.1527 4839.8015) (3131.9084 4836.8702) (3136.9771 4833.0229) (3142.6107 4829.7405)
      (3147.6947 4828.2748) (3151.1145 4829.2977) (3152.1374 4832.7176) (3150.6718 4837.8015) (3147.3893 4843.4351)
      (3143.5267 4848.5038) (3140.5954 4852.2595) (3139.8626 4854.5038) (3141.9695 4855.5725) (3146.7023 4856.1527)
      (3153.0229 4857.0229) (3159.3282 4858.687) (3163.9542 4861.2366) (3165.6489 4864.3817) (3163.9542 4867.5267)
      (3159.3282 4870.0763) (3153.0229 4871.7405) (3146.7023 4872.5954) (3141.9695 4873.1908) (3139.8626 4874.2595)
      (3140.5954 4876.5038) (3143.5267 4880.2595) (3147.3893 4885.3282) (3150.6718 4890.9618) (3152.1374 4896.0458)
      (3151.1145 4899.4656) (3147.6947 4900.4885) (3142.6107 4899.0229) (3136.9771 4895.7405) (3131.9084 4891.8779)
      (3128.1527 4888.9466) (3125.9084 4888.2137) (3124.8397 4890.3206) (3124.2443 4895.0534) (3123.3893 4901.3588)
      (3121.7252 4907.6641) (3119.1756 4912.3053) (3116.0305 4914.0) (3112.8855 4912.3053) (3110.3359 4907.6641)
      (3108.6718 4901.3588) (3107.8168 4895.0534) (3107.2214 4890.3206) (3106.1527 4888.2137) (3103.9084 4888.9466)
      (3100.1527 4891.8779) (3095.084 4895.7405) (3089.4504 4899.0229) (3084.3664 4900.4885) (3080.9466 4899.4656)
      (3079.9237 4896.0458) (3081.3893 4890.9618) (3084.6718 4885.3282) (3088.5344 4880.2595) (3091.4656 4876.5038)
      (3092.1985 4874.2595) (3090.0916 4873.1908) (3085.3588 4872.5954) (3079.0382 4871.7405) (3072.7328 4870.0763)
      (3068.1069 4867.5267)
    ))
    ; P2449 -- see feature_dimensions_mm.csv
    ("06_ORNAMENT" 1 (
      (3066.4122 4552.9313) (3068.1069 4549.7863) (3072.7328 4547.2366) (3079.0382 4545.5725) (3085.3588 4544.7023)
      (3090.0916 4544.1221) (3092.1985 4543.0534) (3091.4656 4540.8092) (3088.5344 4537.0534) (3084.6718 4531.9847)
      (3081.3893 4526.3511) (3079.9237 4521.2672) (3080.9466 4517.8473) (3084.3664 4516.8244) (3089.4504 4518.2901)
      (3095.084 4521.5725) (3100.1527 4525.4198) (3103.9084 4528.3511) (3106.1527 4529.084) (3107.2214 4526.9924)
      (3107.8168 4522.2595) (3108.6718 4515.9389) (3110.3359 4509.6336) (3112.8855 4505.0076) (3116.0305 4503.313)
      (3119.1756 4505.0076) (3121.7252 4509.6336) (3123.3893 4515.9389) (3124.2443 4522.2595) (3124.8397 4526.9924)
      (3125.9084 4529.084) (3128.1527 4528.3511) (3131.9084 4525.4198) (3136.9771 4521.5725) (3142.6107 4518.2901)
      (3147.6947 4516.8244) (3151.1145 4517.8473) (3152.1374 4521.2672) (3150.6718 4526.3511) (3147.3893 4531.9847)
      (3143.5267 4537.0534) (3140.5954 4540.8092) (3139.8626 4543.0534) (3141.9695 4544.1221) (3146.7023 4544.7023)
      (3153.0229 4545.5725) (3159.3282 4547.2366) (3163.9542 4549.7863) (3165.6489 4552.9313) (3163.9542 4556.0763)
      (3159.3282 4558.626) (3153.0229 4560.2901) (3146.7023 4561.145) (3141.9695 4561.7405) (3139.8626 4562.8092)
      (3140.5954 4565.0534) (3143.5267 4568.8092) (3147.3893 4573.8779) (3150.6718 4579.5115) (3152.1374 4584.5954)
      (3151.1145 4588.0153) (3147.6947 4589.0382) (3142.6107 4587.5725) (3136.9771 4584.2901) (3131.9084 4580.4275)
      (3128.1527 4577.4962) (3125.9084 4576.7634) (3124.8397 4578.8702) (3124.2443 4583.6031) (3123.3893 4589.9084)
      (3121.7252 4596.2137) (3119.1756 4600.855) (3116.0305 4602.5496) (3112.8855 4600.855) (3110.3359 4596.2137)
      (3108.6718 4589.9084) (3107.8168 4583.6031) (3107.2214 4578.8702) (3106.1527 4576.7634) (3103.9084 4577.4962)
      (3100.1527 4580.4275) (3095.084 4584.2901) (3089.4504 4587.5725) (3084.3664 4589.0382) (3080.9466 4588.0153)
      (3079.9237 4584.5954) (3081.3893 4579.5115) (3084.6718 4573.8779) (3088.5344 4568.8092) (3091.4656 4565.0534)
      (3092.1985 4562.8092) (3090.0916 4561.7405) (3085.3588 4561.145) (3079.0382 4560.2901) (3072.7328 4558.626)
      (3068.1069 4556.0763)
    ))
    ; P2450 -- see feature_dimensions_mm.csv
    ("06_ORNAMENT" 1 (
      (3066.4122 4241.4809) (3068.1069 4238.3359) (3072.7328 4235.7863) (3079.0382 4234.1221) (3085.3588 4233.2519)
      (3090.0916 4232.6718) (3092.1985 4231.6031) (3091.4656 4229.3588) (3088.5344 4225.6031) (3084.6718 4220.5344)
      (3081.3893 4214.9008) (3079.9237 4209.8168) (3080.9466 4206.3969) (3084.3664 4205.374) (3089.4504 4206.8397)
      (3095.084 4210.1221) (3100.1527 4213.9695) (3103.9084 4216.9008) (3106.1527 4217.6336) (3107.2214 4215.542)
      (3107.8168 4210.8092) (3108.6718 4204.4885) (3110.3359 4198.1832) (3112.8855 4193.5573) (3116.0305 4191.8626)
      (3119.1756 4193.5573) (3121.7252 4198.1832) (3123.3893 4204.4885) (3124.2443 4210.8092) (3124.8397 4215.542)
      (3125.9084 4217.6336) (3128.1527 4216.9008) (3131.9084 4213.9695) (3136.9771 4210.1221) (3142.6107 4206.8397)
      (3147.6947 4205.374) (3151.1145 4206.3969) (3152.1374 4209.8168) (3150.6718 4214.9008) (3147.3893 4220.5344)
      (3143.5267 4225.6031) (3140.5954 4229.3588) (3139.8626 4231.6031) (3141.9695 4232.6718) (3146.7023 4233.2519)
      (3153.0229 4234.1221) (3159.3282 4235.7863) (3163.9542 4238.3359) (3165.6489 4241.4809) (3163.9542 4244.626)
      (3159.3282 4247.1756) (3153.0229 4248.8397) (3146.7023 4249.6947) (3141.9695 4250.2901) (3139.8626 4251.3588)
      (3140.5954 4253.6031) (3143.5267 4257.3588) (3147.3893 4262.4275) (3150.6718 4268.0611) (3152.1374 4273.145)
      (3151.1145 4276.5649) (3147.6947 4277.5878) (3142.6107 4276.1221) (3136.9771 4272.8397) (3131.9084 4268.9771)
      (3128.1527 4266.0458) (3125.9084 4265.313) (3124.8397 4267.4198) (3124.2443 4272.1527) (3123.3893 4278.458)
      (3121.7252 4284.7634) (3119.1756 4289.4046) (3116.0305 4291.0992) (3112.8855 4289.4046) (3110.3359 4284.7634)
      (3108.6718 4278.458) (3107.8168 4272.1527) (3107.2214 4267.4198) (3106.1527 4265.313) (3103.9084 4266.0458)
      (3100.1527 4268.9771) (3095.084 4272.8397) (3089.4504 4276.1221) (3084.3664 4277.5878) (3080.9466 4276.5649)
      (3079.9237 4273.145) (3081.3893 4268.0611) (3084.6718 4262.4275) (3088.5344 4257.3588) (3091.4656 4253.6031)
      (3092.1985 4251.3588) (3090.0916 4250.2901) (3085.3588 4249.6947) (3079.0382 4248.8397) (3072.7328 4247.1756)
      (3068.1069 4244.626)
    ))
    ; P2451 -- see feature_dimensions_mm.csv
    ("06_ORNAMENT" 1 (
      (3066.4122 3930.0305) (3068.1069 3926.8855) (3072.7328 3924.3359) (3079.0382 3922.6718) (3085.3588 3921.8015)
      (3090.0916 3921.2214) (3092.1985 3920.1527) (3091.4656 3917.9084) (3088.5344 3914.1527) (3084.6718 3909.084)
      (3081.3893 3903.4504) (3079.9237 3898.3664) (3080.9466 3894.9466) (3084.3664 3893.9237) (3089.4504 3895.3893)
      (3095.084 3898.6718) (3100.1527 3902.5191) (3103.9084 3905.4504) (3106.1527 3906.1832) (3107.2214 3904.0916)
      (3107.8168 3899.3588) (3108.6718 3893.0382) (3110.3359 3886.7328) (3112.8855 3882.1069) (3116.0305 3880.4122)
      (3119.1756 3882.1069) (3121.7252 3886.7328) (3123.3893 3893.0382) (3124.2443 3899.3588) (3124.8397 3904.0916)
      (3125.9084 3906.1832) (3128.1527 3905.4504) (3131.9084 3902.5191) (3136.9771 3898.6718) (3142.6107 3895.3893)
      (3147.6947 3893.9237) (3151.1145 3894.9466) (3152.1374 3898.3664) (3150.6718 3903.4504) (3147.3893 3909.084)
      (3143.5267 3914.1527) (3140.5954 3917.9084) (3139.8626 3920.1527) (3141.9695 3921.2214) (3146.7023 3921.8015)
      (3153.0229 3922.6718) (3159.3282 3924.3359) (3163.9542 3926.8855) (3165.6489 3930.0305) (3163.9542 3933.1756)
      (3159.3282 3935.7252) (3153.0229 3937.3893) (3146.7023 3938.2443) (3141.9695 3938.8397) (3139.8626 3939.9084)
      (3140.5954 3942.1527) (3143.5267 3945.9084) (3147.3893 3950.9771) (3150.6718 3956.6107) (3152.1374 3961.6947)
      (3151.1145 3965.1145) (3147.6947 3966.1374) (3142.6107 3964.6718) (3136.9771 3961.3893) (3131.9084 3957.5267)
      (3128.1527 3954.5954) (3125.9084 3953.8626) (3124.8397 3955.9695) (3124.2443 3960.7023) (3123.3893 3967.0076)
      (3121.7252 3973.313) (3119.1756 3977.9542) (3116.0305 3979.6489) (3112.8855 3977.9542) (3110.3359 3973.313)
      (3108.6718 3967.0076) (3107.8168 3960.7023) (3107.2214 3955.9695) (3106.1527 3953.8626) (3103.9084 3954.5954)
      (3100.1527 3957.5267) (3095.084 3961.3893) (3089.4504 3964.6718) (3084.3664 3966.1374) (3080.9466 3965.1145)
      (3079.9237 3961.6947) (3081.3893 3956.6107) (3084.6718 3950.9771) (3088.5344 3945.9084) (3091.4656 3942.1527)
      (3092.1985 3939.9084) (3090.0916 3938.8397) (3085.3588 3938.2443) (3079.0382 3937.3893) (3072.7328 3935.7252)
      (3068.1069 3933.1756)
    ))
    ; P2452 -- see feature_dimensions_mm.csv
    ("06_ORNAMENT" 1 (
      (3097.7099 5253.6947) (3116.0305 5233.084) (3134.3511 5253.6947) (3116.0305 5274.3053)
    ))
    ; P2453 -- see feature_dimensions_mm.csv
    ("06_ORNAMENT" 1 (
      (3097.7099 4942.2443) (3116.0305 4921.6336) (3134.3511 4942.2443) (3116.0305 4962.855)
    ))
    ; P2454 -- see feature_dimensions_mm.csv
    ("06_ORNAMENT" 1 (
      (3097.7099 4630.7939) (3116.0305 4610.1832) (3134.3511 4630.7939) (3116.0305 4651.4046)
    ))
    ; P2455 -- see feature_dimensions_mm.csv
    ("06_ORNAMENT" 1 (
      (3097.7099 4319.3435) (3116.0305 4298.7328) (3134.3511 4319.3435) (3116.0305 4339.9542)
    ))
    ; P2456 -- see feature_dimensions_mm.csv
    ("06_ORNAMENT" 1 (
      (3097.7099 4007.8931) (3116.0305 3987.2824) (3134.3511 4007.8931) (3116.0305 4028.5038)
    ))
    ; P2457 -- see feature_dimensions_mm.csv
    ("06_ORNAMENT" 1 (
      (3104.1221 5487.2824) (3105.0229 5482.7176) (3107.6031 5478.855) (3111.4809 5476.2748) (3116.0305 5475.374)
      (3120.5802 5476.2748) (3124.458 5478.855) (3127.0382 5482.7176) (3127.9389 5487.2824) (3127.0382 5491.8321)
      (3124.458 5495.6947) (3120.5802 5498.2748) (3116.0305 5499.1908) (3111.4809 5498.2748) (3107.6031 5495.6947)
      (3105.0229 5491.8321)
    ))
    ; P2458 -- see feature_dimensions_mm.csv
    ("06_ORNAMENT" 1 (
      (3104.1221 5175.8321) (3105.0229 5171.2672) (3107.6031 5167.4046) (3111.4809 5164.8244) (3116.0305 5163.9237)
      (3120.5802 5164.8244) (3124.458 5167.4046) (3127.0382 5171.2672) (3127.9389 5175.8321) (3127.0382 5180.3817)
      (3124.458 5184.2443) (3120.5802 5186.8244) (3116.0305 5187.7405) (3111.4809 5186.8244) (3107.6031 5184.2443)
      (3105.0229 5180.3817)
    ))
    ; P2459 -- see feature_dimensions_mm.csv
    ("06_ORNAMENT" 1 (
      (3104.1221 4864.3817) (3105.0229 4859.8168) (3107.6031 4855.9542) (3111.4809 4853.374) (3116.0305 4852.4733)
      (3120.5802 4853.374) (3124.458 4855.9542) (3127.0382 4859.8168) (3127.9389 4864.3817) (3127.0382 4868.9313)
      (3124.458 4872.7939) (3120.5802 4875.374) (3116.0305 4876.2901) (3111.4809 4875.374) (3107.6031 4872.7939)
      (3105.0229 4868.9313)
    ))
    ; P2460 -- see feature_dimensions_mm.csv
    ("06_ORNAMENT" 1 (
      (3104.1221 4552.9313) (3105.0229 4548.3664) (3107.6031 4544.5038) (3111.4809 4541.9237) (3116.0305 4541.0229)
      (3120.5802 4541.9237) (3124.458 4544.5038) (3127.0382 4548.3664) (3127.9389 4552.9313) (3127.0382 4557.4809)
      (3124.458 4561.3435) (3120.5802 4563.9237) (3116.0305 4564.8397) (3111.4809 4563.9237) (3107.6031 4561.3435)
      (3105.0229 4557.4809)
    ))
    ; P2461 -- see feature_dimensions_mm.csv
    ("06_ORNAMENT" 1 (
      (3104.1221 4241.4809) (3105.0229 4236.916) (3107.6031 4233.0534) (3111.4809 4230.4733) (3116.0305 4229.5725)
      (3120.5802 4230.4733) (3124.458 4233.0534) (3127.0382 4236.916) (3127.9389 4241.4809) (3127.0382 4246.0305)
      (3124.458 4249.8931) (3120.5802 4252.4733) (3116.0305 4253.3893) (3111.4809 4252.4733) (3107.6031 4249.8931)
      (3105.0229 4246.0305)
    ))
    ; P2462 -- see feature_dimensions_mm.csv
    ("06_ORNAMENT" 1 (
      (3104.1221 3930.0305) (3105.0229 3925.4656) (3107.6031 3921.6031) (3111.4809 3919.0229) (3116.0305 3918.1221)
      (3120.5802 3919.0229) (3124.458 3921.6031) (3127.0382 3925.4656) (3127.9389 3930.0305) (3127.0382 3934.5802)
      (3124.458 3938.4427) (3120.5802 3941.0229) (3116.0305 3941.9389) (3111.4809 3941.0229) (3107.6031 3938.4427)
      (3105.0229 3934.5802)
    ))
    ; P2463 -- see feature_dimensions_mm.csv
    ("06_ORNAMENT" 1 (
      (3106.2443 5827.8321) (3120.6412 5825.2214) (3111.771 5834.5344) (3108.3206 5837.6641)
    ))
    ; P2464 -- see feature_dimensions_mm.csv
    ("06_ORNAMENT" 1 (
      (3144.2748 5331.5573) (3145.9695 5328.4122) (3150.5954 5325.8626) (3156.9008 5324.1985) (3163.2214 5323.3282)
      (3167.9542 5322.7481) (3170.0611 5321.6794) (3169.3282 5319.4351) (3166.3969 5315.6794) (3162.5344 5310.6107)
      (3159.2519 5304.9771) (3157.7863 5299.8931) (3158.8092 5296.4733) (3162.229 5295.4504) (3167.313 5296.916)
      (3172.9466 5300.1985) (3178.0153 5304.0458) (3181.771 5306.9771) (3184.0153 5307.7099) (3185.084 5305.6183)
      (3185.6794 5300.8855) (3186.5344 5294.5649) (3188.1985 5288.2595) (3190.7481 5283.6336) (3193.8931 5281.9389)
      (3197.0382 5283.6336) (3199.5878 5288.2595) (3201.2519 5294.5649) (3202.1069 5300.8855) (3202.7023 5305.6183)
      (3203.771 5307.7099) (3206.0153 5306.9771) (3209.771 5304.0458) (3214.8397 5300.1985) (3220.4733 5296.916)
      (3225.5573 5295.4504) (3228.9771 5296.4733) (3230.0 5299.8931) (3228.5344 5304.9771) (3225.2519 5310.6107)
      (3221.3893 5315.6794) (3218.458 5319.4351) (3217.7252 5321.6794) (3219.8321 5322.7481) (3224.5649 5323.3282)
      (3230.8855 5324.1985) (3237.1908 5325.8626) (3241.8168 5328.4122) (3243.5115 5331.5573) (3241.8168 5334.7023)
      (3237.1908 5337.2519) (3230.8855 5338.916) (3224.5649 5339.771) (3219.8321 5340.3664) (3217.7252 5341.4351)
      (3218.458 5343.6794) (3221.3893 5347.4351) (3225.2519 5352.5038) (3228.5344 5358.1374) (3230.0 5363.2214)
      (3228.9771 5366.6412) (3225.5573 5367.6641) (3220.4733 5366.1985) (3214.8397 5362.916) (3209.771 5359.0534)
      (3206.0153 5356.1221) (3203.771 5355.3893) (3202.7023 5357.4962) (3202.1069 5362.229) (3201.2519 5368.5344)
      (3199.5878 5374.8397) (3197.0382 5379.4809) (3193.8931 5381.1756) (3190.7481 5379.4809) (3188.1985 5374.8397)
      (3186.5344 5368.5344) (3185.6794 5362.229) (3185.084 5357.4962) (3184.0153 5355.3893) (3181.771 5356.1221)
      (3178.0153 5359.0534) (3172.9466 5362.916) (3167.313 5366.1985) (3162.229 5367.6641) (3158.8092 5366.6412)
      (3157.7863 5363.2214) (3159.2519 5358.1374) (3162.5344 5352.5038) (3166.3969 5347.4351) (3169.3282 5343.6794)
      (3170.0611 5341.4351) (3167.9542 5340.3664) (3163.2214 5339.771) (3156.9008 5338.916) (3150.5954 5337.2519)
      (3145.9695 5334.7023)
    ))
    ; P2465 -- see feature_dimensions_mm.csv
    ("06_ORNAMENT" 1 (
      (3144.2748 5020.1069) (3145.9695 5016.9618) (3150.5954 5014.4122) (3156.9008 5012.7481) (3163.2214 5011.8779)
      (3167.9542 5011.2977) (3170.0611 5010.229) (3169.3282 5007.9847) (3166.3969 5004.229) (3162.5344 4999.1603)
      (3159.2519 4993.5267) (3157.7863 4988.4427) (3158.8092 4985.0229) (3162.229 4984.0) (3167.313 4985.4656)
      (3172.9466 4988.7481) (3178.0153 4992.5954) (3181.771 4995.5267) (3184.0153 4996.2595) (3185.084 4994.1679)
      (3185.6794 4989.4351) (3186.5344 4983.1145) (3188.1985 4976.8092) (3190.7481 4972.1832) (3193.8931 4970.4885)
      (3197.0382 4972.1832) (3199.5878 4976.8092) (3201.2519 4983.1145) (3202.1069 4989.4351) (3202.7023 4994.1679)
      (3203.771 4996.2595) (3206.0153 4995.5267) (3209.771 4992.5954) (3214.8397 4988.7481) (3220.4733 4985.4656)
      (3225.5573 4984.0) (3228.9771 4985.0229) (3230.0 4988.4427) (3228.5344 4993.5267) (3225.2519 4999.1603)
      (3221.3893 5004.229) (3218.458 5007.9847) (3217.7252 5010.229) (3219.8321 5011.2977) (3224.5649 5011.8779)
      (3230.8855 5012.7481) (3237.1908 5014.4122) (3241.8168 5016.9618) (3243.5115 5020.1069) (3241.8168 5023.2519)
      (3237.1908 5025.8015) (3230.8855 5027.4656) (3224.5649 5028.3206) (3219.8321 5028.916) (3217.7252 5029.9847)
      (3218.458 5032.229) (3221.3893 5035.9847) (3225.2519 5041.0534) (3228.5344 5046.687) (3230.0 5051.771)
      (3228.9771 5055.1908) (3225.5573 5056.2137) (3220.4733 5054.7481) (3214.8397 5051.4656) (3209.771 5047.6031)
      (3206.0153 5044.6718) (3203.771 5043.9389) (3202.7023 5046.0458) (3202.1069 5050.7786) (3201.2519 5057.084)
      (3199.5878 5063.3893) (3197.0382 5068.0305) (3193.8931 5069.7252) (3190.7481 5068.0305) (3188.1985 5063.3893)
      (3186.5344 5057.084) (3185.6794 5050.7786) (3185.084 5046.0458) (3184.0153 5043.9389) (3181.771 5044.6718)
      (3178.0153 5047.6031) (3172.9466 5051.4656) (3167.313 5054.7481) (3162.229 5056.2137) (3158.8092 5055.1908)
      (3157.7863 5051.771) (3159.2519 5046.687) (3162.5344 5041.0534) (3166.3969 5035.9847) (3169.3282 5032.229)
      (3170.0611 5029.9847) (3167.9542 5028.916) (3163.2214 5028.3206) (3156.9008 5027.4656) (3150.5954 5025.8015)
      (3145.9695 5023.2519)
    ))
    ; P2466 -- see feature_dimensions_mm.csv
    ("06_ORNAMENT" 1 (
      (3144.2748 4708.6565) (3145.9695 4705.5115) (3150.5954 4702.9618) (3156.9008 4701.2977) (3163.2214 4700.4275)
      (3167.9542 4699.8473) (3170.0611 4698.7786) (3169.3282 4696.5344) (3166.3969 4692.7786) (3162.5344 4687.7099)
      (3159.2519 4682.0763) (3157.7863 4676.9924) (3158.8092 4673.5725) (3162.229 4672.5496) (3167.313 4674.0153)
      (3172.9466 4677.2977) (3178.0153 4681.145) (3181.771 4684.0763) (3184.0153 4684.8092) (3185.084 4682.7176)
      (3185.6794 4677.9847) (3186.5344 4671.6641) (3188.1985 4665.3588) (3190.7481 4660.7328) (3193.8931 4659.0382)
      (3197.0382 4660.7328) (3199.5878 4665.3588) (3201.2519 4671.6641) (3202.1069 4677.9847) (3202.7023 4682.7176)
      (3203.771 4684.8092) (3206.0153 4684.0763) (3209.771 4681.145) (3214.8397 4677.2977) (3220.4733 4674.0153)
      (3225.5573 4672.5496) (3228.9771 4673.5725) (3230.0 4676.9924) (3228.5344 4682.0763) (3225.2519 4687.7099)
      (3221.3893 4692.7786) (3218.458 4696.5344) (3217.7252 4698.7786) (3219.8321 4699.8473) (3224.5649 4700.4275)
      (3230.8855 4701.2977) (3237.1908 4702.9618) (3241.8168 4705.5115) (3243.5115 4708.6565) (3241.8168 4711.8015)
      (3237.1908 4714.3511) (3230.8855 4716.0153) (3224.5649 4716.8702) (3219.8321 4717.4656) (3217.7252 4718.5344)
      (3218.458 4720.7786) (3221.3893 4724.5344) (3225.2519 4729.6031) (3228.5344 4735.2366) (3230.0 4740.3206)
      (3228.9771 4743.7405) (3225.5573 4744.7634) (3220.4733 4743.2977) (3214.8397 4740.0153) (3209.771 4736.1527)
      (3206.0153 4733.2214) (3203.771 4732.4885) (3202.7023 4734.5954) (3202.1069 4739.3282) (3201.2519 4745.6336)
      (3199.5878 4751.9389) (3197.0382 4756.5802) (3193.8931 4758.2748) (3190.7481 4756.5802) (3188.1985 4751.9389)
      (3186.5344 4745.6336) (3185.6794 4739.3282) (3185.084 4734.5954) (3184.0153 4732.4885) (3181.771 4733.2214)
      (3178.0153 4736.1527) (3172.9466 4740.0153) (3167.313 4743.2977) (3162.229 4744.7634) (3158.8092 4743.7405)
      (3157.7863 4740.3206) (3159.2519 4735.2366) (3162.5344 4729.6031) (3166.3969 4724.5344) (3169.3282 4720.7786)
      (3170.0611 4718.5344) (3167.9542 4717.4656) (3163.2214 4716.8702) (3156.9008 4716.0153) (3150.5954 4714.3511)
      (3145.9695 4711.8015)
    ))
    ; P2467 -- see feature_dimensions_mm.csv
    ("06_ORNAMENT" 1 (
      (3144.2748 4085.7557) (3145.9695 4082.6107) (3150.5954 4080.0611) (3156.9008 4078.3969) (3163.2214 4077.5267)
      (3167.9542 4076.9466) (3170.0611 4075.8779) (3169.3282 4073.6336) (3166.3969 4069.8779) (3162.5344 4064.8092)
      (3159.2519 4059.1756) (3157.7863 4054.0916) (3158.8092 4050.6718) (3162.229 4049.6489) (3167.313 4051.1145)
      (3172.9466 4054.3969) (3178.0153 4058.2595) (3181.771 4061.1756) (3184.0153 4061.9084) (3185.084 4059.8168)
      (3185.6794 4055.084) (3186.5344 4048.7634) (3188.1985 4042.458) (3190.7481 4037.8321) (3193.8931 4036.1374)
      (3197.0382 4037.8321) (3199.5878 4042.458) (3201.2519 4048.7634) (3202.1069 4055.084) (3202.7023 4059.8168)
      (3203.771 4061.9084) (3206.0153 4061.1756) (3209.771 4058.2595) (3214.8397 4054.3969) (3220.4733 4051.1145)
      (3225.5573 4049.6489) (3228.9771 4050.6718) (3230.0 4054.0916) (3228.5344 4059.1756) (3225.2519 4064.8092)
      (3221.3893 4069.8779) (3218.458 4073.6336) (3217.7252 4075.8779) (3219.8321 4076.9466) (3224.5649 4077.5267)
      (3230.8855 4078.3969) (3237.1908 4080.0611) (3241.8168 4082.6107) (3243.5115 4085.7557) (3241.8168 4088.9008)
      (3237.1908 4091.4504) (3230.8855 4093.1145) (3224.5649 4093.9695) (3219.8321 4094.5649) (3217.7252 4095.6336)
      (3218.458 4097.8779) (3221.3893 4101.6336) (3225.2519 4106.7023) (3228.5344 4112.3359) (3230.0 4117.4198)
      (3228.9771 4120.8397) (3225.5573 4121.8626) (3220.4733 4120.3969) (3214.8397 4117.1145) (3209.771 4113.2519)
      (3206.0153 4110.3206) (3203.771 4109.5878) (3202.7023 4111.6947) (3202.1069 4116.4275) (3201.2519 4122.7328)
      (3199.5878 4129.0382) (3197.0382 4133.6794) (3193.8931 4135.374) (3190.7481 4133.6794) (3188.1985 4129.0382)
      (3186.5344 4122.7328) (3185.6794 4116.4275) (3185.084 4111.6947) (3184.0153 4109.5878) (3181.771 4110.3206)
      (3178.0153 4113.2519) (3172.9466 4117.1145) (3167.313 4120.3969) (3162.229 4121.8626) (3158.8092 4120.8397)
      (3157.7863 4117.4198) (3159.2519 4112.3359) (3162.5344 4106.7023) (3166.3969 4101.6336) (3169.3282 4097.8779)
      (3170.0611 4095.6336) (3167.9542 4094.5649) (3163.2214 4093.9695) (3156.9008 4093.1145) (3150.5954 4091.4504)
      (3145.9695 4088.9008)
    ))
    ; P2468 -- see feature_dimensions_mm.csv
    ("06_ORNAMENT" 1 (
      (3155.4809 5898.3053) (3160.6107 5877.084) (3168.5496 5856.7023) (3178.9924 5837.2824) (3191.6183 5818.9313)
      (3198.9313 5810.229) (3242.0153 5801.2061) (3242.7023 5801.0534) (3293.1298 5789.6794) (3293.8626 5789.4962)
      (3338.8397 5778.5649) (3333.0382 5787.6794) (3320.0305 5805.313) (3305.6031 5822.2443) (3289.9084 5838.1832)
      (3273.0534 5852.8702) (3255.2061 5866.0) (3236.4733 5877.2824) (3216.9924 5886.4427) (3215.5115 5886.9313)
      (3219.8321 5886.7023) (3242.0763 5887.9695) (3264.3053 5891.4198) (3286.2595 5896.855) (3307.6794 5904.0458)
      (3328.3206 5912.7786) (3347.9542 5922.8397) (3366.2901 5934.0153) (3383.1145 5946.0763) (3398.1374 5958.8092)
      (3411.145 5972.0) (3414.626 5976.3511) (3425.8473 5972.9771) (3439.7863 5970.4885) (3451.7863 5968.9618)
      (3460.3817 5967.2824) (3464.8397 5964.2748) (3465.2214 5958.916) (3462.3664 5950.626) (3457.6947 5939.4656)
      (3452.8702 5926.1527) (3449.542 5912.0) (3448.9466 5898.6565) (3451.771 5887.8321) (3452.0763 5887.5115)
      (3438.4122 5881.9084) (3419.8626 5871.6794) (3402.9924 5859.2672) (3388.0763 5844.6107) (3388.9618 5822.7786)
      (3392.7786 5801.2519) (3399.2214 5780.1679) (3407.7252 5760.4122) (3450.8397 5748.1679) (3451.8321 5747.8779)
      (3503.374 5731.9695) (3504.4885 5731.6031) (3530.4427 5722.8702) (3520.4885 5740.7023) (3508.1985 5759.4198)
      (3494.5344 5777.0992) (3479.5725 5793.4504) (3463.4046 5808.1832) (3446.0916 5820.9618) (3444.7481 5821.7405)
      (3448.9313 5820.6718) (3470.9924 5817.5725) (3493.4656 5816.6107) (3516.0458 5817.6641) (3538.4733 5820.5344)
      (3560.4275 5825.084) (3581.6336 5831.1298) (3601.8015 5838.5038) (3620.6565 5847.0534) (3637.8779 5856.6107)
      (3653.2061 5866.9924) (3666.3359 5878.0763) (3649.3282 5885.5115) (3630.687 5891.8321) (3610.687 5896.9008)
      (3604.3206 5898.0305) (3604.4885 5898.6565) (3603.8931 5912.0) (3600.5649 5926.1527) (3595.7405 5939.4656)
      (3591.0687 5950.626) (3588.2137 5958.916) (3588.5954 5964.2748) (3593.0534 5967.2824) (3601.6489 5968.9618)
      (3613.6489 5970.4885) (3627.5878 5972.9771) (3641.5115 5977.1603) (3653.374 5983.3282) (3661.3282 5991.1756)
      (3664.1221 6000.0) (3661.3282 6008.8244) (3653.374 6016.6718) (3641.5115 6022.8397) (3627.5878 6027.0229)
      (3613.6489 6029.5115) (3601.6489 6031.0382) (3593.0534 6032.7176) (3588.5954 6035.7252) (3588.2137 6041.084)
      (3591.0687 6049.374) (3595.7405 6060.5344) (3600.5649 6073.8473) (3603.8931 6088.0) (3604.4885 6101.3435)
      (3601.6641 6112.1679) (3595.4198 6118.9924) (3586.3817 6120.9771) (3575.6031 6118.0153) (3564.3359 6110.8397)
      (3553.7405 6100.8702) (3544.626 6090.0458) (3537.2977 6080.4122) (3531.5573 6073.8015) (3526.7176 6071.4504)
      (3521.8779 6073.8015) (3516.1374 6080.4122) (3508.8092 6090.0458) (3499.6947 6100.8702) (3489.0992 6110.8397)
      (3477.8321 6118.0153) (3467.0534 6120.9771) (3458.0153 6118.9924) (3451.771 6112.1679) (3448.9466 6101.3435)
      (3449.542 6088.0) (3452.8702 6073.8473) (3457.6947 6060.5344) (3462.3664 6049.374) (3465.2214 6041.084)
      (3464.8397 6035.7252) (3460.3817 6032.7176) (3451.7863 6031.0382) (3439.7863 6029.5115) (3425.8473 6027.0229)
      (3411.9237 6022.8397) (3400.0611 6016.6718) (3392.1069 6008.8244) (3389.313 6000.0) (3392.1069 5991.1756)
      (3392.4122 5990.8855) (3384.2137 5991.9542) (3363.6031 5993.0229) (3342.229 5992.6107) (3320.4122 5990.6412)
      (3298.458 5987.0992) (3276.6718 5981.9695) (3255.374 5975.1908) (3234.8855 5966.7481) (3215.5115 5956.5954)
      (3197.5725 5944.7176) (3181.374 5931.0687) (3167.2366 5915.6031)
    ))
    ; P2469 -- see feature_dimensions_mm.csv
    ("06_ORNAMENT" 1 (
      (3160.3053 7374.0458) (3221.374 7343.5115) (3282.4427 7374.0458) (3221.374 7404.5802)
    ))
    ; P2470 -- see feature_dimensions_mm.csv
    ("06_ORNAMENT" 1 (
      (3160.3053 7282.4427) (3221.374 7251.9084) (3282.4427 7282.4427) (3221.374 7312.9771)
    ))
    ; P2471 -- see feature_dimensions_mm.csv
    ("06_ORNAMENT" 1 (
      (3160.3053 7190.8397) (3221.374 7160.3053) (3282.4427 7190.8397) (3221.374 7221.374)
    ))
    ; P2472 -- see feature_dimensions_mm.csv
    ("06_ORNAMENT" 1 (
      (3175.5725 5409.4198) (3193.8931 5388.8092) (3212.2137 5409.4198) (3193.8931 5430.0305)
    ))
    ; P2473 -- see feature_dimensions_mm.csv
    ("06_ORNAMENT" 1 (
      (3175.5725 5097.9695) (3193.8931 5077.3588) (3212.2137 5097.9695) (3193.8931 5118.5802)
    ))
    ; P2474 -- see feature_dimensions_mm.csv
    ("06_ORNAMENT" 1 (
      (3175.5725 4786.5191) (3193.8931 4765.9084) (3212.2137 4786.5191) (3193.8931 4807.1298)
    ))
    ; P2475 -- see feature_dimensions_mm.csv
    ("06_ORNAMENT" 1 (
      (3175.5725 4163.6183) (3193.8931 4143.0076) (3212.2137 4163.6183) (3193.8931 4184.229)
    ))
    ; P2476 -- see feature_dimensions_mm.csv
    ("06_ORNAMENT" 1 (
      (3181.9847 5331.5573) (3182.8855 5326.9924) (3185.4656 5323.1298) (3189.3435 5320.5496) (3193.8931 5319.6489)
      (3198.4427 5320.5496) (3202.3206 5323.1298) (3204.9008 5326.9924) (3205.8015 5331.5573) (3204.9008 5336.1069)
      (3202.3206 5339.9695) (3198.4427 5342.5496) (3193.8931 5343.4656) (3189.3435 5342.5496) (3185.4656 5339.9695)
      (3182.8855 5336.1069)
    ))
    ; P2477 -- see feature_dimensions_mm.csv
    ("06_ORNAMENT" 1 (
      (3181.9847 5020.1069) (3182.8855 5015.542) (3185.4656 5011.6794) (3189.3435 5009.0992) (3193.8931 5008.1985)
      (3198.4427 5009.0992) (3202.3206 5011.6794) (3204.9008 5015.542) (3205.8015 5020.1069) (3204.9008 5024.6565)
      (3202.3206 5028.5191) (3198.4427 5031.0992) (3193.8931 5032.0153) (3189.3435 5031.0992) (3185.4656 5028.5191)
      (3182.8855 5024.6565)
    ))
    ; P2478 -- see feature_dimensions_mm.csv
    ("06_ORNAMENT" 1 (
      (3181.9847 4708.6565) (3182.8855 4704.0916) (3185.4656 4700.229) (3189.3435 4697.6489) (3193.8931 4696.7481)
      (3198.4427 4697.6489) (3202.3206 4700.229) (3204.9008 4704.0916) (3205.8015 4708.6565) (3204.9008 4713.2061)
      (3202.3206 4717.0687) (3198.4427 4719.6489) (3193.8931 4720.5649) (3189.3435 4719.6489) (3185.4656 4717.0687)
      (3182.8855 4713.2061)
    ))
    ; P2479 -- see feature_dimensions_mm.csv
    ("06_ORNAMENT" 1 (
      (3181.9847 4397.2061) (3182.8855 4392.6412) (3185.4656 4388.7786) (3189.3435 4386.1985) (3193.8931 4385.2977)
      (3198.4427 4386.1985) (3202.3206 4388.7786) (3204.9008 4392.6412) (3205.8015 4397.2061) (3204.9008 4401.7557)
      (3202.3206 4405.6183) (3198.4427 4408.1985) (3193.8931 4409.1145) (3189.3435 4408.1985) (3185.4656 4405.6183)
      (3182.8855 4401.7557)
    ))
    ; P2480 -- see feature_dimensions_mm.csv
    ("06_ORNAMENT" 1 (
      (3181.9847 4085.7557) (3182.8855 4081.1908) (3185.4656 4077.3282) (3189.3435 4074.7481) (3193.8931 4073.8473)
      (3198.4427 4074.7481) (3202.3206 4077.3282) (3204.9008 4081.1908) (3205.8015 4085.7557) (3204.9008 4090.3053)
      (3202.3206 4094.1679) (3198.4427 4096.7481) (3193.8931 4097.6641) (3189.3435 4096.7481) (3185.4656 4094.1679)
      (3182.8855 4090.3053)
    ))
    ; P2481 -- see feature_dimensions_mm.csv
    ("06_ORNAMENT" 1 (
      (3222.1374 5175.8321) (3223.8321 5172.687) (3228.458 5170.1374) (3234.7634 5168.4733) (3241.084 5167.6031)
      (3245.8168 5167.0229) (3247.9237 5165.9542) (3247.1908 5163.7099) (3244.2595 5159.9542) (3240.3969 5154.8855)
      (3237.1145 5149.2519) (3235.6489 5144.1679) (3236.6718 5140.7481) (3240.0916 5139.7252) (3245.1756 5141.1908)
      (3250.8092 5144.4733) (3255.8779 5148.3206) (3259.6336 5151.2519) (3261.8779 5151.9847) (3262.9466 5149.8931)
      (3263.542 5145.1603) (3264.3969 5138.8397) (3266.0611 5132.5344) (3268.6107 5127.9084) (3271.7557 5126.2137)
      (3274.9008 5127.9084) (3277.4504 5132.5344) (3279.1145 5138.8397) (3279.9695 5145.1603) (3280.5649 5149.8931)
      (3281.6336 5151.9847) (3283.8779 5151.2519) (3287.6336 5148.3206) (3292.7023 5144.4733) (3298.3359 5141.1908)
      (3303.4198 5139.7252) (3306.8397 5140.7481) (3307.8626 5144.1679) (3306.3969 5149.2519) (3303.1145 5154.8855)
      (3299.2519 5159.9542) (3296.3206 5163.7099) (3295.5878 5165.9542) (3297.6947 5167.0229) (3302.4275 5167.6031)
      (3308.7481 5168.4733) (3315.0534 5170.1374) (3319.6794 5172.687) (3321.374 5175.8321) (3319.6794 5178.9771)
      (3315.0534 5181.5267) (3308.7481 5183.1908) (3302.4275 5184.0458) (3297.6947 5184.6412) (3295.5878 5185.7099)
      (3296.3206 5187.9542) (3299.2519 5191.7099) (3303.1145 5196.7786) (3306.3969 5202.4122) (3307.8626 5207.4962)
      (3306.8397 5210.916) (3303.4198 5211.9389) (3298.3359 5210.4733) (3292.7023 5207.1908) (3287.6336 5203.3282)
      (3283.8779 5200.3969) (3281.6336 5199.6641) (3280.5649 5201.771) (3279.9695 5206.5038) (3279.1145 5212.8092)
      (3277.4504 5219.1145) (3274.9008 5223.7557) (3271.7557 5225.4504) (3268.6107 5223.7557) (3266.0611 5219.1145)
      (3264.3969 5212.8092) (3263.542 5206.5038) (3262.9466 5201.771) (3261.8779 5199.6641) (3259.6336 5200.3969)
      (3255.8779 5203.3282) (3250.8092 5207.1908) (3245.1756 5210.4733) (3240.0916 5211.9389) (3236.6718 5210.916)
      (3235.6489 5207.4962) (3237.1145 5202.4122) (3240.3969 5196.7786) (3244.2595 5191.7099) (3247.1908 5187.9542)
      (3247.9237 5185.7099) (3245.8168 5184.6412) (3241.084 5184.0458) (3234.7634 5183.1908) (3228.458 5181.5267)
      (3223.8321 5178.9771)
    ))
    ; P2482 -- see feature_dimensions_mm.csv
    ("06_ORNAMENT" 1 (
      (3222.1374 4864.3817) (3223.8321 4861.2366) (3228.458 4858.687) (3234.7634 4857.0229) (3241.084 4856.1527)
      (3245.8168 4855.5725) (3247.9237 4854.5038) (3247.1908 4852.2595) (3244.2595 4848.5038) (3240.3969 4843.4351)
      (3237.1145 4837.8015) (3235.6489 4832.7176) (3236.6718 4829.2977) (3240.0916 4828.2748) (3245.1756 4829.7405)
      (3250.8092 4833.0229) (3255.8779 4836.8702) (3259.6336 4839.8015) (3261.8779 4840.5344) (3262.9466 4838.4427)
      (3263.542 4833.7099) (3264.3969 4827.3893) (3266.0611 4821.084) (3268.6107 4816.458) (3271.7557 4814.7634)
      (3274.9008 4816.458) (3277.4504 4821.084) (3279.1145 4827.3893) (3279.9695 4833.7099) (3280.5649 4838.4427)
      (3281.6336 4840.5344) (3283.8779 4839.8015) (3287.6336 4836.8702) (3292.7023 4833.0229) (3298.3359 4829.7405)
      (3303.4198 4828.2748) (3306.8397 4829.2977) (3307.8626 4832.7176) (3306.3969 4837.8015) (3303.1145 4843.4351)
      (3299.2519 4848.5038) (3296.3206 4852.2595) (3295.5878 4854.5038) (3297.6947 4855.5725) (3302.4275 4856.1527)
      (3308.7481 4857.0229) (3315.0534 4858.687) (3319.6794 4861.2366) (3321.374 4864.3817) (3319.6794 4867.5267)
      (3315.0534 4870.0763) (3308.7481 4871.7405) (3302.4275 4872.5954) (3297.6947 4873.1908) (3295.5878 4874.2595)
      (3296.3206 4876.5038) (3299.2519 4880.2595) (3303.1145 4885.3282) (3306.3969 4890.9618) (3307.8626 4896.0458)
      (3306.8397 4899.4656) (3303.4198 4900.4885) (3298.3359 4899.0229) (3292.7023 4895.7405) (3287.6336 4891.8779)
      (3283.8779 4888.9466) (3281.6336 4888.2137) (3280.5649 4890.3206) (3279.9695 4895.0534) (3279.1145 4901.3588)
      (3277.4504 4907.6641) (3274.9008 4912.3053) (3271.7557 4914.0) (3268.6107 4912.3053) (3266.0611 4907.6641)
      (3264.3969 4901.3588) (3263.542 4895.0534) (3262.9466 4890.3206) (3261.8779 4888.2137) (3259.6336 4888.9466)
      (3255.8779 4891.8779) (3250.8092 4895.7405) (3245.1756 4899.0229) (3240.0916 4900.4885) (3236.6718 4899.4656)
      (3235.6489 4896.0458) (3237.1145 4890.9618) (3240.3969 4885.3282) (3244.2595 4880.2595) (3247.1908 4876.5038)
      (3247.9237 4874.2595) (3245.8168 4873.1908) (3241.084 4872.5954) (3234.7634 4871.7405) (3228.458 4870.0763)
      (3223.8321 4867.5267)
    ))
    ; P2483 -- see feature_dimensions_mm.csv
    ("06_ORNAMENT" 1 (
      (3222.1374 4552.9313) (3223.8321 4549.7863) (3228.458 4547.2366) (3234.7634 4545.5725) (3241.084 4544.7023)
      (3245.8168 4544.1221) (3247.9237 4543.0534) (3247.1908 4540.8092) (3244.2595 4537.0534) (3240.3969 4531.9847)
      (3237.1145 4526.3511) (3235.6489 4521.2672) (3236.6718 4517.8473) (3240.0916 4516.8244) (3245.1756 4518.2901)
      (3250.8092 4521.5725) (3255.8779 4525.4198) (3259.6336 4528.3511) (3261.8779 4529.084) (3262.9466 4526.9924)
      (3263.542 4522.2595) (3264.3969 4515.9389) (3266.0611 4509.6336) (3268.6107 4505.0076) (3271.7557 4503.313)
      (3274.9008 4505.0076) (3277.4504 4509.6336) (3279.1145 4515.9389) (3279.9695 4522.2595) (3280.5649 4526.9924)
      (3281.6336 4529.084) (3283.8779 4528.3511) (3287.6336 4525.4198) (3292.7023 4521.5725) (3298.3359 4518.2901)
      (3303.4198 4516.8244) (3306.8397 4517.8473) (3307.8626 4521.2672) (3306.3969 4526.3511) (3303.1145 4531.9847)
      (3299.2519 4537.0534) (3296.3206 4540.8092) (3295.5878 4543.0534) (3297.6947 4544.1221) (3302.4275 4544.7023)
      (3308.7481 4545.5725) (3315.0534 4547.2366) (3319.6794 4549.7863) (3321.374 4552.9313) (3319.6794 4556.0763)
      (3315.0534 4558.626) (3308.7481 4560.2901) (3302.4275 4561.145) (3297.6947 4561.7405) (3295.5878 4562.8092)
      (3296.3206 4565.0534) (3299.2519 4568.8092) (3303.1145 4573.8779) (3306.3969 4579.5115) (3307.8626 4584.5954)
      (3306.8397 4588.0153) (3303.4198 4589.0382) (3298.3359 4587.5725) (3292.7023 4584.2901) (3287.6336 4580.4275)
      (3283.8779 4577.4962) (3281.6336 4576.7634) (3280.5649 4578.8702) (3279.9695 4583.6031) (3279.1145 4589.9084)
      (3277.4504 4596.2137) (3274.9008 4600.855) (3271.7557 4602.5496) (3268.6107 4600.855) (3266.0611 4596.2137)
      (3264.3969 4589.9084) (3263.542 4583.6031) (3262.9466 4578.8702) (3261.8779 4576.7634) (3259.6336 4577.4962)
      (3255.8779 4580.4275) (3250.8092 4584.2901) (3245.1756 4587.5725) (3240.0916 4589.0382) (3236.6718 4588.0153)
      (3235.6489 4584.5954) (3237.1145 4579.5115) (3240.3969 4573.8779) (3244.2595 4568.8092) (3247.1908 4565.0534)
      (3247.9237 4562.8092) (3245.8168 4561.7405) (3241.084 4561.145) (3234.7634 4560.2901) (3228.458 4558.626)
      (3223.8321 4556.0763)
    ))
    ; P2484 -- see feature_dimensions_mm.csv
    ("06_ORNAMENT" 1 (
      (3222.1374 4241.4809) (3223.8321 4238.3359) (3228.458 4235.7863) (3234.7634 4234.1221) (3241.084 4233.2519)
      (3245.8168 4232.6718) (3247.9237 4231.6031) (3247.1908 4229.3588) (3244.2595 4225.6031) (3240.3969 4220.5344)
      (3237.1145 4214.9008) (3235.6489 4209.8168) (3236.6718 4206.3969) (3240.0916 4205.374) (3245.1756 4206.8397)
      (3250.8092 4210.1221) (3255.8779 4213.9695) (3259.6336 4216.9008) (3261.8779 4217.6336) (3262.9466 4215.542)
      (3263.542 4210.8092) (3264.3969 4204.4885) (3266.0611 4198.1832) (3268.6107 4193.5573) (3271.7557 4191.8626)
      (3274.9008 4193.5573) (3277.4504 4198.1832) (3279.1145 4204.4885) (3279.9695 4210.8092) (3280.5649 4215.542)
      (3281.6336 4217.6336) (3283.8779 4216.9008) (3287.6336 4213.9695) (3292.7023 4210.1221) (3298.3359 4206.8397)
      (3303.4198 4205.374) (3306.8397 4206.3969) (3307.8626 4209.8168) (3306.3969 4214.9008) (3303.1145 4220.5344)
      (3299.2519 4225.6031) (3296.3206 4229.3588) (3295.5878 4231.6031) (3297.6947 4232.6718) (3302.4275 4233.2519)
      (3308.7481 4234.1221) (3315.0534 4235.7863) (3319.6794 4238.3359) (3321.374 4241.4809) (3319.6794 4244.626)
      (3315.0534 4247.1756) (3308.7481 4248.8397) (3302.4275 4249.6947) (3297.6947 4250.2901) (3295.5878 4251.3588)
      (3296.3206 4253.6031) (3299.2519 4257.3588) (3303.1145 4262.4275) (3306.3969 4268.0611) (3307.8626 4273.145)
      (3306.8397 4276.5649) (3303.4198 4277.5878) (3298.3359 4276.1221) (3292.7023 4272.8397) (3287.6336 4268.9771)
      (3283.8779 4266.0458) (3281.6336 4265.313) (3280.5649 4267.4198) (3279.9695 4272.1527) (3279.1145 4278.458)
      (3277.4504 4284.7634) (3274.9008 4289.4046) (3271.7557 4291.0992) (3268.6107 4289.4046) (3266.0611 4284.7634)
      (3264.3969 4278.458) (3263.542 4272.1527) (3262.9466 4267.4198) (3261.8779 4265.313) (3259.6336 4266.0458)
      (3255.8779 4268.9771) (3250.8092 4272.8397) (3245.1756 4276.1221) (3240.0916 4277.5878) (3236.6718 4276.5649)
      (3235.6489 4273.145) (3237.1145 4268.0611) (3240.3969 4262.4275) (3244.2595 4257.3588) (3247.1908 4253.6031)
      (3247.9237 4251.3588) (3245.8168 4250.2901) (3241.084 4249.6947) (3234.7634 4248.8397) (3228.458 4247.1756)
      (3223.8321 4244.626)
    ))
    ; P2485 -- see feature_dimensions_mm.csv
    ("06_ORNAMENT" 1 (
      (3222.1374 3930.0305) (3223.8321 3926.8855) (3228.458 3924.3359) (3234.7634 3922.6718) (3241.084 3921.8015)
      (3245.8168 3921.2214) (3247.9237 3920.1527) (3247.1908 3917.9084) (3244.2595 3914.1527) (3240.3969 3909.084)
      (3237.1145 3903.4504) (3235.6489 3898.3664) (3236.6718 3894.9466) (3240.0916 3893.9237) (3245.1756 3895.3893)
      (3250.8092 3898.6718) (3255.8779 3902.5191) (3259.6336 3905.4504) (3261.8779 3906.1832) (3262.9466 3904.0916)
      (3263.542 3899.3588) (3264.3969 3893.0382) (3266.0611 3886.7328) (3268.6107 3882.1069) (3271.7557 3880.4122)
      (3274.9008 3882.1069) (3277.4504 3886.7328) (3279.1145 3893.0382) (3279.9695 3899.3588) (3280.5649 3904.0916)
      (3281.6336 3906.1832) (3283.8779 3905.4504) (3287.6336 3902.5191) (3292.7023 3898.6718) (3298.3359 3895.3893)
      (3303.4198 3893.9237) (3306.8397 3894.9466) (3307.8626 3898.3664) (3306.3969 3903.4504) (3303.1145 3909.084)
      (3299.2519 3914.1527) (3296.3206 3917.9084) (3295.5878 3920.1527) (3297.6947 3921.2214) (3302.4275 3921.8015)
      (3308.7481 3922.6718) (3315.0534 3924.3359) (3319.6794 3926.8855) (3321.374 3930.0305) (3319.6794 3933.1756)
      (3315.0534 3935.7252) (3308.7481 3937.3893) (3302.4275 3938.2443) (3297.6947 3938.8397) (3295.5878 3939.9084)
      (3296.3206 3942.1527) (3299.2519 3945.9084) (3303.1145 3950.9771) (3306.3969 3956.6107) (3307.8626 3961.6947)
      (3306.8397 3965.1145) (3303.4198 3966.1374) (3298.3359 3964.6718) (3292.7023 3961.3893) (3287.6336 3957.5267)
      (3283.8779 3954.5954) (3281.6336 3953.8626) (3280.5649 3955.9695) (3279.9695 3960.7023) (3279.1145 3967.0076)
      (3277.4504 3973.313) (3274.9008 3977.9542) (3271.7557 3979.6489) (3268.6107 3977.9542) (3266.0611 3973.313)
      (3264.3969 3967.0076) (3263.542 3960.7023) (3262.9466 3955.9695) (3261.8779 3953.8626) (3259.6336 3954.5954)
      (3255.8779 3957.5267) (3250.8092 3961.3893) (3245.1756 3964.6718) (3240.0916 3966.1374) (3236.6718 3965.1145)
      (3235.6489 3961.6947) (3237.1145 3956.6107) (3240.3969 3950.9771) (3244.2595 3945.9084) (3247.1908 3942.1527)
      (3247.9237 3939.9084) (3245.8168 3938.8397) (3241.084 3938.2443) (3234.7634 3937.3893) (3228.458 3935.7252)
      (3223.8321 3933.1756)
    ))
    ; P2486 -- see feature_dimensions_mm.csv
    ("06_ORNAMENT" 1 (
      (3253.4351 5253.6947) (3271.7557 5233.084) (3290.0763 5253.6947) (3271.7557 5274.3053)
    ))
    ; P2487 -- see feature_dimensions_mm.csv
    ("06_ORNAMENT" 1 (
      (3253.4351 4942.2443) (3271.7557 4921.6336) (3290.0763 4942.2443) (3271.7557 4962.855)
    ))
    ; P2488 -- see feature_dimensions_mm.csv
    ("06_ORNAMENT" 1 (
      (3253.4351 4630.7939) (3271.7557 4610.1832) (3290.0763 4630.7939) (3271.7557 4651.4046)
    ))
    ; P2489 -- see feature_dimensions_mm.csv
    ("06_ORNAMENT" 1 (
      (3253.4351 4319.3435) (3271.7557 4298.7328) (3290.0763 4319.3435) (3271.7557 4339.9542)
    ))
    ; P2490 -- see feature_dimensions_mm.csv
    ("06_ORNAMENT" 1 (
      (3253.4351 4007.8931) (3271.7557 3987.2824) (3290.0763 4007.8931) (3271.7557 4028.5038)
    ))
    ; P2491 -- see feature_dimensions_mm.csv
    ("06_ORNAMENT" 1 (
      (3259.8473 5487.2824) (3260.7481 5482.7176) (3263.3282 5478.855) (3267.2061 5476.2748) (3271.7557 5475.374)
      (3276.3053 5476.2748) (3280.1832 5478.855) (3282.7634 5482.7176) (3283.6641 5487.2824) (3282.7634 5491.8321)
      (3280.1832 5495.6947) (3276.3053 5498.2748) (3271.7557 5499.1908) (3267.2061 5498.2748) (3263.3282 5495.6947)
      (3260.7481 5491.8321)
    ))
    ; P2492 -- see feature_dimensions_mm.csv
    ("06_ORNAMENT" 1 (
      (3259.8473 5175.8321) (3260.7481 5171.2672) (3263.3282 5167.4046) (3267.2061 5164.8244) (3271.7557 5163.9237)
      (3276.3053 5164.8244) (3280.1832 5167.4046) (3282.7634 5171.2672) (3283.6641 5175.8321) (3282.7634 5180.3817)
      (3280.1832 5184.2443) (3276.3053 5186.8244) (3271.7557 5187.7405) (3267.2061 5186.8244) (3263.3282 5184.2443)
      (3260.7481 5180.3817)
    ))
    ; P2493 -- see feature_dimensions_mm.csv
    ("06_ORNAMENT" 1 (
      (3259.8473 4864.3817) (3260.7481 4859.8168) (3263.3282 4855.9542) (3267.2061 4853.374) (3271.7557 4852.4733)
      (3276.3053 4853.374) (3280.1832 4855.9542) (3282.7634 4859.8168) (3283.6641 4864.3817) (3282.7634 4868.9313)
      (3280.1832 4872.7939) (3276.3053 4875.374) (3271.7557 4876.2901) (3267.2061 4875.374) (3263.3282 4872.7939)
      (3260.7481 4868.9313)
    ))
    ; P2494 -- see feature_dimensions_mm.csv
    ("06_ORNAMENT" 1 (
      (3259.8473 4552.9313) (3260.7481 4548.3664) (3263.3282 4544.5038) (3267.2061 4541.9237) (3271.7557 4541.0229)
      (3276.3053 4541.9237) (3280.1832 4544.5038) (3282.7634 4548.3664) (3283.6641 4552.9313) (3282.7634 4557.4809)
      (3280.1832 4561.3435) (3276.3053 4563.9237) (3271.7557 4564.8397) (3267.2061 4563.9237) (3263.3282 4561.3435)
      (3260.7481 4557.4809)
    ))
    ; P2495 -- see feature_dimensions_mm.csv
    ("06_ORNAMENT" 1 (
      (3259.8473 4241.4809) (3260.7481 4236.916) (3263.3282 4233.0534) (3267.2061 4230.4733) (3271.7557 4229.5725)
      (3276.3053 4230.4733) (3280.1832 4233.0534) (3282.7634 4236.916) (3283.6641 4241.4809) (3282.7634 4246.0305)
      (3280.1832 4249.8931) (3276.3053 4252.4733) (3271.7557 4253.3893) (3267.2061 4252.4733) (3263.3282 4249.8931)
      (3260.7481 4246.0305)
    ))
    ; P2496 -- see feature_dimensions_mm.csv
    ("06_ORNAMENT" 1 (
      (3259.8473 3930.0305) (3260.7481 3925.4656) (3263.3282 3921.6031) (3267.2061 3919.0229) (3271.7557 3918.1221)
      (3276.3053 3919.0229) (3280.1832 3921.6031) (3282.7634 3925.4656) (3283.6641 3930.0305) (3282.7634 3934.5802)
      (3280.1832 3938.4427) (3276.3053 3941.0229) (3271.7557 3941.9389) (3267.2061 3941.0229) (3263.3282 3938.4427)
      (3260.7481 3934.5802)
    ))
    ; P2497 -- see feature_dimensions_mm.csv
    ("06_ORNAMENT" 1 (
      (3300.0 5331.5573) (3301.6947 5328.4122) (3306.3206 5325.8626) (3312.626 5324.1985) (3318.9466 5323.3282)
      (3323.6794 5322.7481) (3325.7863 5321.6794) (3325.0534 5319.4351) (3322.1221 5315.6794) (3318.2595 5310.6107)
      (3314.9771 5304.9771) (3313.5115 5299.8931) (3314.5344 5296.4733) (3317.9542 5295.4504) (3323.0382 5296.916)
      (3328.6718 5300.1985) (3333.7405 5304.0458) (3337.4962 5306.9771) (3339.7405 5307.7099) (3340.8092 5305.6183)
      (3341.4046 5300.8855) (3342.2595 5294.5649) (3343.9237 5288.2595) (3346.4733 5283.6336) (3349.6183 5281.9389)
      (3352.7634 5283.6336) (3355.313 5288.2595) (3356.9771 5294.5649) (3357.8321 5300.8855) (3358.4275 5305.6183)
      (3359.4962 5307.7099) (3361.7405 5306.9771) (3365.4962 5304.0458) (3370.5649 5300.1985) (3376.1985 5296.916)
      (3381.2824 5295.4504) (3384.7023 5296.4733) (3385.7252 5299.8931) (3384.2595 5304.9771) (3380.9771 5310.6107)
      (3377.1145 5315.6794) (3374.1832 5319.4351) (3373.4504 5321.6794) (3375.5573 5322.7481) (3380.2901 5323.3282)
      (3386.6107 5324.1985) (3392.916 5325.8626) (3397.542 5328.4122) (3399.2366 5331.5573) (3397.542 5334.7023)
      (3392.916 5337.2519) (3386.6107 5338.916) (3380.2901 5339.771) (3375.5573 5340.3664) (3373.4504 5341.4351)
      (3374.1832 5343.6794) (3377.1145 5347.4351) (3380.9771 5352.5038) (3384.2595 5358.1374) (3385.7252 5363.2214)
      (3384.7023 5366.6412) (3381.2824 5367.6641) (3376.1985 5366.1985) (3370.5649 5362.916) (3365.4962 5359.0534)
      (3361.7405 5356.1221) (3359.4962 5355.3893) (3358.4275 5357.4962) (3357.8321 5362.229) (3356.9771 5368.5344)
      (3355.313 5374.8397) (3352.7634 5379.4809) (3349.6183 5381.1756) (3346.4733 5379.4809) (3343.9237 5374.8397)
      (3342.2595 5368.5344) (3341.4046 5362.229) (3340.8092 5357.4962) (3339.7405 5355.3893) (3337.4962 5356.1221)
      (3333.7405 5359.0534) (3328.6718 5362.916) (3323.0382 5366.1985) (3317.9542 5367.6641) (3314.5344 5366.6412)
      (3313.5115 5363.2214) (3314.9771 5358.1374) (3318.2595 5352.5038) (3322.1221 5347.4351) (3325.0534 5343.6794)
      (3325.7863 5341.4351) (3323.6794 5340.3664) (3318.9466 5339.771) (3312.626 5338.916) (3306.3206 5337.2519)
      (3301.6947 5334.7023)
    ))
    ; P2498 -- see feature_dimensions_mm.csv
    ("06_ORNAMENT" 1 (
      (3300.0 5020.1069) (3301.6947 5016.9618) (3306.3206 5014.4122) (3312.626 5012.7481) (3318.9466 5011.8779)
      (3323.6794 5011.2977) (3325.7863 5010.229) (3325.0534 5007.9847) (3322.1221 5004.229) (3318.2595 4999.1603)
      (3314.9771 4993.5267) (3313.5115 4988.4427) (3314.5344 4985.0229) (3317.9542 4984.0) (3323.0382 4985.4656)
      (3328.6718 4988.7481) (3333.7405 4992.5954) (3337.4962 4995.5267) (3339.7405 4996.2595) (3340.8092 4994.1679)
      (3341.4046 4989.4351) (3342.2595 4983.1145) (3343.9237 4976.8092) (3346.4733 4972.1832) (3349.6183 4970.4885)
      (3352.7634 4972.1832) (3355.313 4976.8092) (3356.9771 4983.1145) (3357.8321 4989.4351) (3358.4275 4994.1679)
      (3359.4962 4996.2595) (3361.7405 4995.5267) (3365.4962 4992.5954) (3370.5649 4988.7481) (3376.1985 4985.4656)
      (3381.2824 4984.0) (3384.7023 4985.0229) (3385.7252 4988.4427) (3384.2595 4993.5267) (3380.9771 4999.1603)
      (3377.1145 5004.229) (3374.1832 5007.9847) (3373.4504 5010.229) (3375.5573 5011.2977) (3380.2901 5011.8779)
      (3386.6107 5012.7481) (3392.916 5014.4122) (3397.542 5016.9618) (3399.2366 5020.1069) (3397.542 5023.2519)
      (3392.916 5025.8015) (3386.6107 5027.4656) (3380.2901 5028.3206) (3375.5573 5028.916) (3373.4504 5029.9847)
      (3374.1832 5032.229) (3377.1145 5035.9847) (3380.9771 5041.0534) (3384.2595 5046.687) (3385.7252 5051.771)
      (3384.7023 5055.1908) (3381.2824 5056.2137) (3376.1985 5054.7481) (3370.5649 5051.4656) (3365.4962 5047.6031)
      (3361.7405 5044.6718) (3359.4962 5043.9389) (3358.4275 5046.0458) (3357.8321 5050.7786) (3356.9771 5057.084)
      (3355.313 5063.3893) (3352.7634 5068.0305) (3349.6183 5069.7252) (3346.4733 5068.0305) (3343.9237 5063.3893)
      (3342.2595 5057.084) (3341.4046 5050.7786) (3340.8092 5046.0458) (3339.7405 5043.9389) (3337.4962 5044.6718)
      (3333.7405 5047.6031) (3328.6718 5051.4656) (3323.0382 5054.7481) (3317.9542 5056.2137) (3314.5344 5055.1908)
      (3313.5115 5051.771) (3314.9771 5046.687) (3318.2595 5041.0534) (3322.1221 5035.9847) (3325.0534 5032.229)
      (3325.7863 5029.9847) (3323.6794 5028.916) (3318.9466 5028.3206) (3312.626 5027.4656) (3306.3206 5025.8015)
      (3301.6947 5023.2519)
    ))
    ; P2499 -- see feature_dimensions_mm.csv
    ("06_ORNAMENT" 1 (
      (3300.0 4708.6565) (3301.6947 4705.5115) (3306.3206 4702.9618) (3312.626 4701.2977) (3318.9466 4700.4275)
      (3323.6794 4699.8473) (3325.7863 4698.7786) (3325.0534 4696.5344) (3322.1221 4692.7786) (3318.2595 4687.7099)
      (3314.9771 4682.0763) (3313.5115 4676.9924) (3314.5344 4673.5725) (3317.9542 4672.5496) (3323.0382 4674.0153)
      (3328.6718 4677.2977) (3333.7405 4681.145) (3337.4962 4684.0763) (3339.7405 4684.8092) (3340.8092 4682.7176)
      (3341.4046 4677.9847) (3342.2595 4671.6641) (3343.9237 4665.3588) (3346.4733 4660.7328) (3349.6183 4659.0382)
      (3352.7634 4660.7328) (3355.313 4665.3588) (3356.9771 4671.6641) (3357.8321 4677.9847) (3358.4275 4682.7176)
      (3359.4962 4684.8092) (3361.7405 4684.0763) (3365.4962 4681.145) (3370.5649 4677.2977) (3376.1985 4674.0153)
      (3381.2824 4672.5496) (3384.7023 4673.5725) (3385.7252 4676.9924) (3384.2595 4682.0763) (3380.9771 4687.7099)
      (3377.1145 4692.7786) (3374.1832 4696.5344) (3373.4504 4698.7786) (3375.5573 4699.8473) (3380.2901 4700.4275)
      (3386.6107 4701.2977) (3392.916 4702.9618) (3397.542 4705.5115) (3399.2366 4708.6565) (3397.542 4711.8015)
      (3392.916 4714.3511) (3386.6107 4716.0153) (3380.2901 4716.8702) (3375.5573 4717.4656) (3373.4504 4718.5344)
      (3374.1832 4720.7786) (3377.1145 4724.5344) (3380.9771 4729.6031) (3384.2595 4735.2366) (3385.7252 4740.3206)
      (3384.7023 4743.7405) (3381.2824 4744.7634) (3376.1985 4743.2977) (3370.5649 4740.0153) (3365.4962 4736.1527)
      (3361.7405 4733.2214) (3359.4962 4732.4885) (3358.4275 4734.5954) (3357.8321 4739.3282) (3356.9771 4745.6336)
      (3355.313 4751.9389) (3352.7634 4756.5802) (3349.6183 4758.2748) (3346.4733 4756.5802) (3343.9237 4751.9389)
      (3342.2595 4745.6336) (3341.4046 4739.3282) (3340.8092 4734.5954) (3339.7405 4732.4885) (3337.4962 4733.2214)
      (3333.7405 4736.1527) (3328.6718 4740.0153) (3323.0382 4743.2977) (3317.9542 4744.7634) (3314.5344 4743.7405)
      (3313.5115 4740.3206) (3314.9771 4735.2366) (3318.2595 4729.6031) (3322.1221 4724.5344) (3325.0534 4720.7786)
      (3325.7863 4718.5344) (3323.6794 4717.4656) (3318.9466 4716.8702) (3312.626 4716.0153) (3306.3206 4714.3511)
      (3301.6947 4711.8015)
    ))
    ; P2500 -- see feature_dimensions_mm.csv
    ("06_ORNAMENT" 1 (
      (3300.0 4085.7557) (3301.6947 4082.6107) (3306.3206 4080.0611) (3312.626 4078.3969) (3318.9466 4077.5267)
      (3323.6794 4076.9466) (3325.7863 4075.8779) (3325.0534 4073.6336) (3322.1221 4069.8779) (3318.2595 4064.8092)
      (3314.9771 4059.1756) (3313.5115 4054.0916) (3314.5344 4050.6718) (3317.9542 4049.6489) (3323.0382 4051.1145)
      (3328.6718 4054.3969) (3333.7405 4058.2595) (3337.4962 4061.1756) (3339.7405 4061.9084) (3340.8092 4059.8168)
      (3341.4046 4055.084) (3342.2595 4048.7634) (3343.9237 4042.458) (3346.4733 4037.8321) (3349.6183 4036.1374)
      (3352.7634 4037.8321) (3355.313 4042.458) (3356.9771 4048.7634) (3357.8321 4055.084) (3358.4275 4059.8168)
      (3359.4962 4061.9084) (3361.7405 4061.1756) (3365.4962 4058.2595) (3370.5649 4054.3969) (3376.1985 4051.1145)
      (3381.2824 4049.6489) (3384.7023 4050.6718) (3385.7252 4054.0916) (3384.2595 4059.1756) (3380.9771 4064.8092)
      (3377.1145 4069.8779) (3374.1832 4073.6336) (3373.4504 4075.8779) (3375.5573 4076.9466) (3380.2901 4077.5267)
      (3386.6107 4078.3969) (3392.916 4080.0611) (3397.542 4082.6107) (3399.2366 4085.7557) (3397.542 4088.9008)
      (3392.916 4091.4504) (3386.6107 4093.1145) (3380.2901 4093.9695) (3375.5573 4094.5649) (3373.4504 4095.6336)
      (3374.1832 4097.8779) (3377.1145 4101.6336) (3380.9771 4106.7023) (3384.2595 4112.3359) (3385.7252 4117.4198)
      (3384.7023 4120.8397) (3381.2824 4121.8626) (3376.1985 4120.3969) (3370.5649 4117.1145) (3365.4962 4113.2519)
      (3361.7405 4110.3206) (3359.4962 4109.5878) (3358.4275 4111.6947) (3357.8321 4116.4275) (3356.9771 4122.7328)
      (3355.313 4129.0382) (3352.7634 4133.6794) (3349.6183 4135.374) (3346.4733 4133.6794) (3343.9237 4129.0382)
      (3342.2595 4122.7328) (3341.4046 4116.4275) (3340.8092 4111.6947) (3339.7405 4109.5878) (3337.4962 4110.3206)
      (3333.7405 4113.2519) (3328.6718 4117.1145) (3323.0382 4120.3969) (3317.9542 4121.8626) (3314.5344 4120.8397)
      (3313.5115 4117.4198) (3314.9771 4112.3359) (3318.2595 4106.7023) (3322.1221 4101.6336) (3325.0534 4097.8779)
      (3325.7863 4095.6336) (3323.6794 4094.5649) (3318.9466 4093.9695) (3312.626 4093.1145) (3306.3206 4091.4504)
      (3301.6947 4088.9008)
    ))
    ; P2501 -- see feature_dimensions_mm.csv
    ("06_ORNAMENT" 1 (
      (3331.2977 5409.4198) (3349.6183 5388.8092) (3367.9389 5409.4198) (3349.6183 5430.0305)
    ))
    ; P2502 -- see feature_dimensions_mm.csv
    ("06_ORNAMENT" 1 (
      (3331.2977 5097.9695) (3349.6183 5077.3588) (3367.9389 5097.9695) (3349.6183 5118.5802)
    ))
    ; P2503 -- see feature_dimensions_mm.csv
    ("06_ORNAMENT" 1 (
      (3331.2977 4786.5191) (3349.6183 4765.9084) (3367.9389 4786.5191) (3349.6183 4807.1298)
    ))
    ; P2504 -- see feature_dimensions_mm.csv
    ("06_ORNAMENT" 1 (
      (3331.2977 4163.6183) (3349.6183 4143.0076) (3367.9389 4163.6183) (3349.6183 4184.229)
    ))
    ; P2505 -- see feature_dimensions_mm.csv
    ("06_ORNAMENT" 1 (
      (3337.7099 5331.5573) (3338.6107 5326.9924) (3341.1908 5323.1298) (3345.0687 5320.5496) (3349.6183 5319.6489)
      (3354.1679 5320.5496) (3358.0458 5323.1298) (3360.626 5326.9924) (3361.5267 5331.5573) (3360.626 5336.1069)
      (3358.0458 5339.9695) (3354.1679 5342.5496) (3349.6183 5343.4656) (3345.0687 5342.5496) (3341.1908 5339.9695)
      (3338.6107 5336.1069)
    ))
    ; P2506 -- see feature_dimensions_mm.csv
    ("06_ORNAMENT" 1 (
      (3337.7099 5020.1069) (3338.6107 5015.542) (3341.1908 5011.6794) (3345.0687 5009.0992) (3349.6183 5008.1985)
      (3354.1679 5009.0992) (3358.0458 5011.6794) (3360.626 5015.542) (3361.5267 5020.1069) (3360.626 5024.6565)
      (3358.0458 5028.5191) (3354.1679 5031.0992) (3349.6183 5032.0153) (3345.0687 5031.0992) (3341.1908 5028.5191)
      (3338.6107 5024.6565)
    ))
    ; P2507 -- see feature_dimensions_mm.csv
    ("06_ORNAMENT" 1 (
      (3337.7099 4708.6565) (3338.6107 4704.0916) (3341.1908 4700.229) (3345.0687 4697.6489) (3349.6183 4696.7481)
      (3354.1679 4697.6489) (3358.0458 4700.229) (3360.626 4704.0916) (3361.5267 4708.6565) (3360.626 4713.2061)
      (3358.0458 4717.0687) (3354.1679 4719.6489) (3349.6183 4720.5649) (3345.0687 4719.6489) (3341.1908 4717.0687)
      (3338.6107 4713.2061)
    ))
    ; P2508 -- see feature_dimensions_mm.csv
    ("06_ORNAMENT" 1 (
      (3337.7099 4397.2061) (3338.6107 4392.6412) (3341.1908 4388.7786) (3345.0687 4386.1985) (3349.6183 4385.2977)
      (3354.1679 4386.1985) (3358.0458 4388.7786) (3360.626 4392.6412) (3361.5267 4397.2061) (3360.626 4401.7557)
      (3358.0458 4405.6183) (3354.1679 4408.1985) (3349.6183 4409.1145) (3345.0687 4408.1985) (3341.1908 4405.6183)
      (3338.6107 4401.7557)
    ))
    ; P2509 -- see feature_dimensions_mm.csv
    ("06_ORNAMENT" 1 (
      (3337.7099 4085.7557) (3338.6107 4081.1908) (3341.1908 4077.3282) (3345.0687 4074.7481) (3349.6183 4073.8473)
      (3354.1679 4074.7481) (3358.0458 4077.3282) (3360.626 4081.1908) (3361.5267 4085.7557) (3360.626 4090.3053)
      (3358.0458 4094.1679) (3354.1679 4096.7481) (3349.6183 4097.6641) (3345.0687 4096.7481) (3341.1908 4094.1679)
      (3338.6107 4090.3053)
    ))
    ; P2510 -- see feature_dimensions_mm.csv
    ("06_ORNAMENT" 1 (
      (3374.0458 3007.6336) (3404.5802 2977.0992) (3435.1145 3007.6336) (3404.5802 3038.1679)
    ))
    ; P2511 -- see feature_dimensions_mm.csv
    ("06_ORNAMENT" 1 (
      (3374.0458 2916.0305) (3404.5802 2885.4962) (3435.1145 2916.0305) (3404.5802 2946.5649)
    ))
    ; P2512 -- see feature_dimensions_mm.csv
    ("06_ORNAMENT" 1 (
      (3377.8626 5175.8321) (3379.5573 5172.687) (3384.1832 5170.1374) (3390.4885 5168.4733) (3396.8092 5167.6031)
      (3401.542 5167.0229) (3403.6489 5165.9542) (3402.916 5163.7099) (3399.9847 5159.9542) (3396.1221 5154.8855)
      (3392.8397 5149.2519) (3391.374 5144.1679) (3392.3969 5140.7481) (3395.8168 5139.7252) (3400.9008 5141.1908)
      (3406.5344 5144.4733) (3411.6031 5148.3206) (3415.3588 5151.2519) (3417.6031 5151.9847) (3418.6718 5149.8931)
      (3419.2672 5145.1603) (3420.1221 5138.8397) (3421.7863 5132.5344) (3424.3359 5127.9084) (3427.4809 5126.2137)
      (3430.626 5127.9084) (3433.1756 5132.5344) (3434.8397 5138.8397) (3435.6947 5145.1603) (3436.2901 5149.8931)
      (3437.3588 5151.9847) (3439.6031 5151.2519) (3443.3588 5148.3206) (3448.4275 5144.4733) (3454.0611 5141.1908)
      (3459.145 5139.7252) (3462.5649 5140.7481) (3463.5878 5144.1679) (3462.1221 5149.2519) (3458.8397 5154.8855)
      (3454.9771 5159.9542) (3452.0458 5163.7099) (3451.313 5165.9542) (3453.4198 5167.0229) (3458.1527 5167.6031)
      (3464.4733 5168.4733) (3470.7786 5170.1374) (3475.4046 5172.687) (3477.0992 5175.8321) (3475.4046 5178.9771)
      (3470.7786 5181.5267) (3464.4733 5183.1908) (3458.1527 5184.0458) (3453.4198 5184.6412) (3451.313 5185.7099)
      (3452.0458 5187.9542) (3454.9771 5191.7099) (3458.8397 5196.7786) (3462.1221 5202.4122) (3463.5878 5207.4962)
      (3462.5649 5210.916) (3459.145 5211.9389) (3454.0611 5210.4733) (3448.4275 5207.1908) (3443.3588 5203.3282)
      (3439.6031 5200.3969) (3437.3588 5199.6641) (3436.2901 5201.771) (3435.6947 5206.5038) (3434.8397 5212.8092)
      (3433.1756 5219.1145) (3430.626 5223.7557) (3427.4809 5225.4504) (3424.3359 5223.7557) (3421.7863 5219.1145)
      (3420.1221 5212.8092) (3419.2672 5206.5038) (3418.6718 5201.771) (3417.6031 5199.6641) (3415.3588 5200.3969)
      (3411.6031 5203.3282) (3406.5344 5207.1908) (3400.9008 5210.4733) (3395.8168 5211.9389) (3392.3969 5210.916)
      (3391.374 5207.4962) (3392.8397 5202.4122) (3396.1221 5196.7786) (3399.9847 5191.7099) (3402.916 5187.9542)
      (3403.6489 5185.7099) (3401.542 5184.6412) (3396.8092 5184.0458) (3390.4885 5183.1908) (3384.1832 5181.5267)
      (3379.5573 5178.9771)
    ))
    ; P2513 -- see feature_dimensions_mm.csv
    ("06_ORNAMENT" 1 (
      (3377.8626 4864.3817) (3379.5573 4861.2366) (3384.1832 4858.687) (3390.4885 4857.0229) (3396.8092 4856.1527)
      (3401.542 4855.5725) (3403.6489 4854.5038) (3402.916 4852.2595) (3399.9847 4848.5038) (3396.1221 4843.4351)
      (3392.8397 4837.8015) (3391.374 4832.7176) (3392.3969 4829.2977) (3395.8168 4828.2748) (3400.9008 4829.7405)
      (3406.5344 4833.0229) (3411.6031 4836.8702) (3415.3588 4839.8015) (3417.6031 4840.5344) (3418.6718 4838.4427)
      (3419.2672 4833.7099) (3420.1221 4827.3893) (3421.7863 4821.084) (3424.3359 4816.458) (3427.4809 4814.7634)
      (3430.626 4816.458) (3433.1756 4821.084) (3434.8397 4827.3893) (3435.6947 4833.7099) (3436.2901 4838.4427)
      (3437.3588 4840.5344) (3439.6031 4839.8015) (3443.3588 4836.8702) (3448.4275 4833.0229) (3454.0611 4829.7405)
      (3459.145 4828.2748) (3462.5649 4829.2977) (3463.5878 4832.7176) (3462.1221 4837.8015) (3458.8397 4843.4351)
      (3454.9771 4848.5038) (3452.0458 4852.2595) (3451.313 4854.5038) (3453.4198 4855.5725) (3458.1527 4856.1527)
      (3464.4733 4857.0229) (3470.7786 4858.687) (3475.4046 4861.2366) (3477.0992 4864.3817) (3475.4046 4867.5267)
      (3470.7786 4870.0763) (3464.4733 4871.7405) (3458.1527 4872.5954) (3453.4198 4873.1908) (3451.313 4874.2595)
      (3452.0458 4876.5038) (3454.9771 4880.2595) (3458.8397 4885.3282) (3462.1221 4890.9618) (3463.5878 4896.0458)
      (3462.5649 4899.4656) (3459.145 4900.4885) (3454.0611 4899.0229) (3448.4275 4895.7405) (3443.3588 4891.8779)
      (3439.6031 4888.9466) (3437.3588 4888.2137) (3436.2901 4890.3206) (3435.6947 4895.0534) (3434.8397 4901.3588)
      (3433.1756 4907.6641) (3430.626 4912.3053) (3427.4809 4914.0) (3424.3359 4912.3053) (3421.7863 4907.6641)
      (3420.1221 4901.3588) (3419.2672 4895.0534) (3418.6718 4890.3206) (3417.6031 4888.2137) (3415.3588 4888.9466)
      (3411.6031 4891.8779) (3406.5344 4895.7405) (3400.9008 4899.0229) (3395.8168 4900.4885) (3392.3969 4899.4656)
      (3391.374 4896.0458) (3392.8397 4890.9618) (3396.1221 4885.3282) (3399.9847 4880.2595) (3402.916 4876.5038)
      (3403.6489 4874.2595) (3401.542 4873.1908) (3396.8092 4872.5954) (3390.4885 4871.7405) (3384.1832 4870.0763)
      (3379.5573 4867.5267)
    ))
    ; P2514 -- see feature_dimensions_mm.csv
    ("06_ORNAMENT" 1 (
      (3377.8626 4552.9313) (3379.5573 4549.7863) (3384.1832 4547.2366) (3390.4885 4545.5725) (3396.8092 4544.7023)
      (3401.542 4544.1221) (3403.6489 4543.0534) (3402.916 4540.8092) (3399.9847 4537.0534) (3396.1221 4531.9847)
      (3392.8397 4526.3511) (3391.374 4521.2672) (3392.3969 4517.8473) (3395.8168 4516.8244) (3400.9008 4518.2901)
      (3406.5344 4521.5725) (3411.6031 4525.4198) (3415.3588 4528.3511) (3417.6031 4529.084) (3418.6718 4526.9924)
      (3419.2672 4522.2595) (3420.1221 4515.9389) (3421.7863 4509.6336) (3424.3359 4505.0076) (3427.4809 4503.313)
      (3430.626 4505.0076) (3433.1756 4509.6336) (3434.8397 4515.9389) (3435.6947 4522.2595) (3436.2901 4526.9924)
      (3437.3588 4529.084) (3439.6031 4528.3511) (3443.3588 4525.4198) (3448.4275 4521.5725) (3454.0611 4518.2901)
      (3459.145 4516.8244) (3462.5649 4517.8473) (3463.5878 4521.2672) (3462.1221 4526.3511) (3458.8397 4531.9847)
      (3454.9771 4537.0534) (3452.0458 4540.8092) (3451.313 4543.0534) (3453.4198 4544.1221) (3458.1527 4544.7023)
      (3464.4733 4545.5725) (3470.7786 4547.2366) (3475.4046 4549.7863) (3477.0992 4552.9313) (3475.4046 4556.0763)
      (3470.7786 4558.626) (3464.4733 4560.2901) (3458.1527 4561.145) (3453.4198 4561.7405) (3451.313 4562.8092)
      (3452.0458 4565.0534) (3454.9771 4568.8092) (3458.8397 4573.8779) (3462.1221 4579.5115) (3463.5878 4584.5954)
      (3462.5649 4588.0153) (3459.145 4589.0382) (3454.0611 4587.5725) (3448.4275 4584.2901) (3443.3588 4580.4275)
      (3439.6031 4577.4962) (3437.3588 4576.7634) (3436.2901 4578.8702) (3435.6947 4583.6031) (3434.8397 4589.9084)
      (3433.1756 4596.2137) (3430.626 4600.855) (3427.4809 4602.5496) (3424.3359 4600.855) (3421.7863 4596.2137)
      (3420.1221 4589.9084) (3419.2672 4583.6031) (3418.6718 4578.8702) (3417.6031 4576.7634) (3415.3588 4577.4962)
      (3411.6031 4580.4275) (3406.5344 4584.2901) (3400.9008 4587.5725) (3395.8168 4589.0382) (3392.3969 4588.0153)
      (3391.374 4584.5954) (3392.8397 4579.5115) (3396.1221 4573.8779) (3399.9847 4568.8092) (3402.916 4565.0534)
      (3403.6489 4562.8092) (3401.542 4561.7405) (3396.8092 4561.145) (3390.4885 4560.2901) (3384.1832 4558.626)
      (3379.5573 4556.0763)
    ))
    ; P2515 -- see feature_dimensions_mm.csv
    ("06_ORNAMENT" 1 (
      (3377.8626 4241.4809) (3379.5573 4238.3359) (3384.1832 4235.7863) (3390.4885 4234.1221) (3396.8092 4233.2519)
      (3401.542 4232.6718) (3403.6489 4231.6031) (3402.916 4229.3588) (3399.9847 4225.6031) (3396.1221 4220.5344)
      (3392.8397 4214.9008) (3391.374 4209.8168) (3392.3969 4206.3969) (3395.8168 4205.374) (3400.9008 4206.8397)
      (3406.5344 4210.1221) (3411.6031 4213.9695) (3415.3588 4216.9008) (3417.6031 4217.6336) (3418.6718 4215.542)
      (3419.2672 4210.8092) (3420.1221 4204.4885) (3421.7863 4198.1832) (3424.3359 4193.5573) (3427.4809 4191.8626)
      (3430.626 4193.5573) (3433.1756 4198.1832) (3434.8397 4204.4885) (3435.6947 4210.8092) (3436.2901 4215.542)
      (3437.3588 4217.6336) (3439.6031 4216.9008) (3443.3588 4213.9695) (3448.4275 4210.1221) (3454.0611 4206.8397)
      (3459.145 4205.374) (3462.5649 4206.3969) (3463.5878 4209.8168) (3462.1221 4214.9008) (3458.8397 4220.5344)
      (3454.9771 4225.6031) (3452.0458 4229.3588) (3451.313 4231.6031) (3453.4198 4232.6718) (3458.1527 4233.2519)
      (3464.4733 4234.1221) (3470.7786 4235.7863) (3475.4046 4238.3359) (3477.0992 4241.4809) (3475.4046 4244.626)
      (3470.7786 4247.1756) (3464.4733 4248.8397) (3458.1527 4249.6947) (3453.4198 4250.2901) (3451.313 4251.3588)
      (3452.0458 4253.6031) (3454.9771 4257.3588) (3458.8397 4262.4275) (3462.1221 4268.0611) (3463.5878 4273.145)
      (3462.5649 4276.5649) (3459.145 4277.5878) (3454.0611 4276.1221) (3448.4275 4272.8397) (3443.3588 4268.9771)
      (3439.6031 4266.0458) (3437.3588 4265.313) (3436.2901 4267.4198) (3435.6947 4272.1527) (3434.8397 4278.458)
      (3433.1756 4284.7634) (3430.626 4289.4046) (3427.4809 4291.0992) (3424.3359 4289.4046) (3421.7863 4284.7634)
      (3420.1221 4278.458) (3419.2672 4272.1527) (3418.6718 4267.4198) (3417.6031 4265.313) (3415.3588 4266.0458)
      (3411.6031 4268.9771) (3406.5344 4272.8397) (3400.9008 4276.1221) (3395.8168 4277.5878) (3392.3969 4276.5649)
      (3391.374 4273.145) (3392.8397 4268.0611) (3396.1221 4262.4275) (3399.9847 4257.3588) (3402.916 4253.6031)
      (3403.6489 4251.3588) (3401.542 4250.2901) (3396.8092 4249.6947) (3390.4885 4248.8397) (3384.1832 4247.1756)
      (3379.5573 4244.626)
    ))
    ; P2516 -- see feature_dimensions_mm.csv
    ("06_ORNAMENT" 1 (
      (3377.8626 3930.0305) (3379.5573 3926.8855) (3384.1832 3924.3359) (3390.4885 3922.6718) (3396.8092 3921.8015)
      (3401.542 3921.2214) (3403.6489 3920.1527) (3402.916 3917.9084) (3399.9847 3914.1527) (3396.1221 3909.084)
      (3392.8397 3903.4504) (3391.374 3898.3664) (3392.3969 3894.9466) (3395.8168 3893.9237) (3400.9008 3895.3893)
      (3406.5344 3898.6718) (3411.6031 3902.5191) (3415.3588 3905.4504) (3417.6031 3906.1832) (3418.6718 3904.0916)
      (3419.2672 3899.3588) (3420.1221 3893.0382) (3421.7863 3886.7328) (3424.3359 3882.1069) (3427.4809 3880.4122)
      (3430.626 3882.1069) (3433.1756 3886.7328) (3434.8397 3893.0382) (3435.6947 3899.3588) (3436.2901 3904.0916)
      (3437.3588 3906.1832) (3439.6031 3905.4504) (3443.3588 3902.5191) (3448.4275 3898.6718) (3454.0611 3895.3893)
      (3459.145 3893.9237) (3462.5649 3894.9466) (3463.5878 3898.3664) (3462.1221 3903.4504) (3458.8397 3909.084)
      (3454.9771 3914.1527) (3452.0458 3917.9084) (3451.313 3920.1527) (3453.4198 3921.2214) (3458.1527 3921.8015)
      (3464.4733 3922.6718) (3470.7786 3924.3359) (3475.4046 3926.8855) (3477.0992 3930.0305) (3475.4046 3933.1756)
      (3470.7786 3935.7252) (3464.4733 3937.3893) (3458.1527 3938.2443) (3453.4198 3938.8397) (3451.313 3939.9084)
      (3452.0458 3942.1527) (3454.9771 3945.9084) (3458.8397 3950.9771) (3462.1221 3956.6107) (3463.5878 3961.6947)
      (3462.5649 3965.1145) (3459.145 3966.1374) (3454.0611 3964.6718) (3448.4275 3961.3893) (3443.3588 3957.5267)
      (3439.6031 3954.5954) (3437.3588 3953.8626) (3436.2901 3955.9695) (3435.6947 3960.7023) (3434.8397 3967.0076)
      (3433.1756 3973.313) (3430.626 3977.9542) (3427.4809 3979.6489) (3424.3359 3977.9542) (3421.7863 3973.313)
      (3420.1221 3967.0076) (3419.2672 3960.7023) (3418.6718 3955.9695) (3417.6031 3953.8626) (3415.3588 3954.5954)
      (3411.6031 3957.5267) (3406.5344 3961.3893) (3400.9008 3964.6718) (3395.8168 3966.1374) (3392.3969 3965.1145)
      (3391.374 3961.6947) (3392.8397 3956.6107) (3396.1221 3950.9771) (3399.9847 3945.9084) (3402.916 3942.1527)
      (3403.6489 3939.9084) (3401.542 3938.8397) (3396.8092 3938.2443) (3390.4885 3937.3893) (3384.1832 3935.7252)
      (3379.5573 3933.1756)
    ))
    ; P2517 -- see feature_dimensions_mm.csv
    ("06_ORNAMENT" 1 (
      (3409.1603 5253.6947) (3427.4809 5233.084) (3445.8015 5253.6947) (3427.4809 5274.3053)
    ))
    ; P2518 -- see feature_dimensions_mm.csv
    ("06_ORNAMENT" 1 (
      (3409.1603 4942.2443) (3427.4809 4921.6336) (3445.8015 4942.2443) (3427.4809 4962.855)
    ))
    ; P2519 -- see feature_dimensions_mm.csv
    ("06_ORNAMENT" 1 (
      (3409.1603 4630.7939) (3427.4809 4610.1832) (3445.8015 4630.7939) (3427.4809 4651.4046)
    ))
    ; P2520 -- see feature_dimensions_mm.csv
    ("06_ORNAMENT" 1 (
      (3409.1603 4319.3435) (3427.4809 4298.7328) (3445.8015 4319.3435) (3427.4809 4339.9542)
    ))
    ; P2521 -- see feature_dimensions_mm.csv
    ("06_ORNAMENT" 1 (
      (3409.1603 4007.8931) (3427.4809 3987.2824) (3445.8015 4007.8931) (3427.4809 4028.5038)
    ))
    ; P2522 -- see feature_dimensions_mm.csv
    ("06_ORNAMENT" 1 (
      (3415.5725 5175.8321) (3416.4733 5171.2672) (3419.0534 5167.4046) (3422.9313 5164.8244) (3427.4809 5163.9237)
      (3432.0305 5164.8244) (3435.9084 5167.4046) (3438.4885 5171.2672) (3439.3893 5175.8321) (3438.4885 5180.3817)
      (3435.9084 5184.2443) (3432.0305 5186.8244) (3427.4809 5187.7405) (3422.9313 5186.8244) (3419.0534 5184.2443)
      (3416.4733 5180.3817)
    ))
    ; P2523 -- see feature_dimensions_mm.csv
    ("06_ORNAMENT" 1 (
      (3415.5725 4864.3817) (3416.4733 4859.8168) (3419.0534 4855.9542) (3422.9313 4853.374) (3427.4809 4852.4733)
      (3432.0305 4853.374) (3435.9084 4855.9542) (3438.4885 4859.8168) (3439.3893 4864.3817) (3438.4885 4868.9313)
      (3435.9084 4872.7939) (3432.0305 4875.374) (3427.4809 4876.2901) (3422.9313 4875.374) (3419.0534 4872.7939)
      (3416.4733 4868.9313)
    ))
    ; P2524 -- see feature_dimensions_mm.csv
    ("06_ORNAMENT" 1 (
      (3415.5725 4552.9313) (3416.4733 4548.3664) (3419.0534 4544.5038) (3422.9313 4541.9237) (3427.4809 4541.0229)
      (3432.0305 4541.9237) (3435.9084 4544.5038) (3438.4885 4548.3664) (3439.3893 4552.9313) (3438.4885 4557.4809)
      (3435.9084 4561.3435) (3432.0305 4563.9237) (3427.4809 4564.8397) (3422.9313 4563.9237) (3419.0534 4561.3435)
      (3416.4733 4557.4809)
    ))
    ; P2525 -- see feature_dimensions_mm.csv
    ("06_ORNAMENT" 1 (
      (3415.5725 4241.4809) (3416.4733 4236.916) (3419.0534 4233.0534) (3422.9313 4230.4733) (3427.4809 4229.5725)
      (3432.0305 4230.4733) (3435.9084 4233.0534) (3438.4885 4236.916) (3439.3893 4241.4809) (3438.4885 4246.0305)
      (3435.9084 4249.8931) (3432.0305 4252.4733) (3427.4809 4253.3893) (3422.9313 4252.4733) (3419.0534 4249.8931)
      (3416.4733 4246.0305)
    ))
    ; P2526 -- see feature_dimensions_mm.csv
    ("06_ORNAMENT" 1 (
      (3415.5725 3930.0305) (3416.4733 3925.4656) (3419.0534 3921.6031) (3422.9313 3919.0229) (3427.4809 3918.1221)
      (3432.0305 3919.0229) (3435.9084 3921.6031) (3438.4885 3925.4656) (3439.3893 3930.0305) (3438.4885 3934.5802)
      (3435.9084 3938.4427) (3432.0305 3941.0229) (3427.4809 3941.9389) (3422.9313 3941.0229) (3419.0534 3938.4427)
      (3416.4733 3934.5802)
    ))
    ; P2527 -- see feature_dimensions_mm.csv
    ("06_ORNAMENT" 1 (
      (3455.7252 5331.5573) (3457.4198 5328.4122) (3462.0458 5325.8626) (3468.3511 5324.1985) (3474.6718 5323.3282)
      (3479.4046 5322.7481) (3481.5115 5321.6794) (3480.7786 5319.4351) (3477.8473 5315.6794) (3473.9847 5310.6107)
      (3470.7023 5304.9771) (3469.2366 5299.8931) (3470.2595 5296.4733) (3473.6794 5295.4504) (3478.7634 5296.916)
      (3484.3969 5300.1985) (3489.4656 5304.0458) (3493.2214 5306.9771) (3495.4656 5307.7099) (3496.5344 5305.6183)
      (3497.1298 5300.8855) (3497.9847 5294.5649) (3499.6489 5288.2595) (3502.1985 5283.6336) (3505.3435 5281.9389)
      (3508.4885 5283.6336) (3511.0382 5288.2595) (3512.7023 5294.5649) (3513.5573 5300.8855) (3514.1527 5305.6183)
      (3515.2214 5307.7099) (3517.4656 5306.9771) (3521.2214 5304.0458) (3526.2901 5300.1985) (3531.9237 5296.916)
      (3537.0076 5295.4504) (3540.4275 5296.4733) (3541.4504 5299.8931) (3539.9847 5304.9771) (3536.7023 5310.6107)
      (3532.8397 5315.6794) (3529.9084 5319.4351) (3529.1756 5321.6794) (3531.2824 5322.7481) (3536.0153 5323.3282)
      (3542.3359 5324.1985) (3548.6412 5325.8626) (3553.2672 5328.4122) (3554.9618 5331.5573) (3553.2672 5334.7023)
      (3548.6412 5337.2519) (3542.3359 5338.916) (3536.0153 5339.771) (3531.2824 5340.3664) (3529.1756 5341.4351)
      (3529.9084 5343.6794) (3532.8397 5347.4351) (3536.7023 5352.5038) (3539.9847 5358.1374) (3541.4504 5363.2214)
      (3540.4275 5366.6412) (3537.0076 5367.6641) (3531.9237 5366.1985) (3526.2901 5362.916) (3521.2214 5359.0534)
      (3517.4656 5356.1221) (3515.2214 5355.3893) (3514.1527 5357.4962) (3513.5573 5362.229) (3512.7023 5368.5344)
      (3511.0382 5374.8397) (3508.4885 5379.4809) (3505.3435 5381.1756) (3502.1985 5379.4809) (3499.6489 5374.8397)
      (3497.9847 5368.5344) (3497.1298 5362.229) (3496.5344 5357.4962) (3495.4656 5355.3893) (3493.2214 5356.1221)
      (3489.4656 5359.0534) (3484.3969 5362.916) (3478.7634 5366.1985) (3473.6794 5367.6641) (3470.2595 5366.6412)
      (3469.2366 5363.2214) (3470.7023 5358.1374) (3473.9847 5352.5038) (3477.8473 5347.4351) (3480.7786 5343.6794)
      (3481.5115 5341.4351) (3479.4046 5340.3664) (3474.6718 5339.771) (3468.3511 5338.916) (3462.0458 5337.2519)
      (3457.4198 5334.7023)
    ))
    ; P2528 -- see feature_dimensions_mm.csv
    ("06_ORNAMENT" 1 (
      (3455.7252 5020.1069) (3457.4198 5016.9618) (3462.0458 5014.4122) (3468.3511 5012.7481) (3474.6718 5011.8779)
      (3479.4046 5011.2977) (3481.5115 5010.229) (3480.7786 5007.9847) (3477.8473 5004.229) (3473.9847 4999.1603)
      (3470.7023 4993.5267) (3469.2366 4988.4427) (3470.2595 4985.0229) (3473.6794 4984.0) (3478.7634 4985.4656)
      (3484.3969 4988.7481) (3489.4656 4992.5954) (3493.2214 4995.5267) (3495.4656 4996.2595) (3496.5344 4994.1679)
      (3497.1298 4989.4351) (3497.9847 4983.1145) (3499.6489 4976.8092) (3502.1985 4972.1832) (3505.3435 4970.4885)
      (3508.4885 4972.1832) (3511.0382 4976.8092) (3512.7023 4983.1145) (3513.5573 4989.4351) (3514.1527 4994.1679)
      (3515.2214 4996.2595) (3517.4656 4995.5267) (3521.2214 4992.5954) (3526.2901 4988.7481) (3531.9237 4985.4656)
      (3537.0076 4984.0) (3540.4275 4985.0229) (3541.4504 4988.4427) (3539.9847 4993.5267) (3536.7023 4999.1603)
      (3532.8397 5004.229) (3529.9084 5007.9847) (3529.1756 5010.229) (3531.2824 5011.2977) (3536.0153 5011.8779)
      (3542.3359 5012.7481) (3548.6412 5014.4122) (3553.2672 5016.9618) (3554.9618 5020.1069) (3553.2672 5023.2519)
      (3548.6412 5025.8015) (3542.3359 5027.4656) (3536.0153 5028.3206) (3531.2824 5028.916) (3529.1756 5029.9847)
      (3529.9084 5032.229) (3532.8397 5035.9847) (3536.7023 5041.0534) (3539.9847 5046.687) (3541.4504 5051.771)
      (3540.4275 5055.1908) (3537.0076 5056.2137) (3531.9237 5054.7481) (3526.2901 5051.4656) (3521.2214 5047.6031)
      (3517.4656 5044.6718) (3515.2214 5043.9389) (3514.1527 5046.0458) (3513.5573 5050.7786) (3512.7023 5057.084)
      (3511.0382 5063.3893) (3508.4885 5068.0305) (3505.3435 5069.7252) (3502.1985 5068.0305) (3499.6489 5063.3893)
      (3497.9847 5057.084) (3497.1298 5050.7786) (3496.5344 5046.0458) (3495.4656 5043.9389) (3493.2214 5044.6718)
      (3489.4656 5047.6031) (3484.3969 5051.4656) (3478.7634 5054.7481) (3473.6794 5056.2137) (3470.2595 5055.1908)
      (3469.2366 5051.771) (3470.7023 5046.687) (3473.9847 5041.0534) (3477.8473 5035.9847) (3480.7786 5032.229)
      (3481.5115 5029.9847) (3479.4046 5028.916) (3474.6718 5028.3206) (3468.3511 5027.4656) (3462.0458 5025.8015)
      (3457.4198 5023.2519)
    ))
    ; P2529 -- see feature_dimensions_mm.csv
    ("06_ORNAMENT" 1 (
      (3455.7252 4708.6565) (3457.4198 4705.5115) (3462.0458 4702.9618) (3468.3511 4701.2977) (3474.6718 4700.4275)
      (3479.4046 4699.8473) (3481.5115 4698.7786) (3480.7786 4696.5344) (3477.8473 4692.7786) (3473.9847 4687.7099)
      (3470.7023 4682.0763) (3469.2366 4676.9924) (3470.2595 4673.5725) (3473.6794 4672.5496) (3478.7634 4674.0153)
      (3484.3969 4677.2977) (3489.4656 4681.145) (3493.2214 4684.0763) (3495.4656 4684.8092) (3496.5344 4682.7176)
      (3497.1298 4677.9847) (3497.9847 4671.6641) (3499.6489 4665.3588) (3502.1985 4660.7328) (3505.3435 4659.0382)
      (3508.4885 4660.7328) (3511.0382 4665.3588) (3512.7023 4671.6641) (3513.5573 4677.9847) (3514.1527 4682.7176)
      (3515.2214 4684.8092) (3517.4656 4684.0763) (3521.2214 4681.145) (3526.2901 4677.2977) (3531.9237 4674.0153)
      (3537.0076 4672.5496) (3540.4275 4673.5725) (3541.4504 4676.9924) (3539.9847 4682.0763) (3536.7023 4687.7099)
      (3532.8397 4692.7786) (3529.9084 4696.5344) (3529.1756 4698.7786) (3531.2824 4699.8473) (3536.0153 4700.4275)
      (3542.3359 4701.2977) (3548.6412 4702.9618) (3553.2672 4705.5115) (3554.9618 4708.6565) (3553.2672 4711.8015)
      (3548.6412 4714.3511) (3542.3359 4716.0153) (3536.0153 4716.8702) (3531.2824 4717.4656) (3529.1756 4718.5344)
      (3529.9084 4720.7786) (3532.8397 4724.5344) (3536.7023 4729.6031) (3539.9847 4735.2366) (3541.4504 4740.3206)
      (3540.4275 4743.7405) (3537.0076 4744.7634) (3531.9237 4743.2977) (3526.2901 4740.0153) (3521.2214 4736.1527)
      (3517.4656 4733.2214) (3515.2214 4732.4885) (3514.1527 4734.5954) (3513.5573 4739.3282) (3512.7023 4745.6336)
      (3511.0382 4751.9389) (3508.4885 4756.5802) (3505.3435 4758.2748) (3502.1985 4756.5802) (3499.6489 4751.9389)
      (3497.9847 4745.6336) (3497.1298 4739.3282) (3496.5344 4734.5954) (3495.4656 4732.4885) (3493.2214 4733.2214)
      (3489.4656 4736.1527) (3484.3969 4740.0153) (3478.7634 4743.2977) (3473.6794 4744.7634) (3470.2595 4743.7405)
      (3469.2366 4740.3206) (3470.7023 4735.2366) (3473.9847 4729.6031) (3477.8473 4724.5344) (3480.7786 4720.7786)
      (3481.5115 4718.5344) (3479.4046 4717.4656) (3474.6718 4716.8702) (3468.3511 4716.0153) (3462.0458 4714.3511)
      (3457.4198 4711.8015)
    ))
    ; P2530 -- see feature_dimensions_mm.csv
    ("06_ORNAMENT" 1 (
      (3455.7252 4085.7557) (3457.4198 4082.6107) (3462.0458 4080.0611) (3468.3511 4078.3969) (3474.6718 4077.5267)
      (3479.4046 4076.9466) (3481.5115 4075.8779) (3480.7786 4073.6336) (3477.8473 4069.8779) (3473.9847 4064.8092)
      (3470.7023 4059.1756) (3469.2366 4054.0916) (3470.2595 4050.6718) (3473.6794 4049.6489) (3478.7634 4051.1145)
      (3484.3969 4054.3969) (3489.4656 4058.2595) (3493.2214 4061.1756) (3495.4656 4061.9084) (3496.5344 4059.8168)
      (3497.1298 4055.084) (3497.9847 4048.7634) (3499.6489 4042.458) (3502.1985 4037.8321) (3505.3435 4036.1374)
      (3508.4885 4037.8321) (3511.0382 4042.458) (3512.7023 4048.7634) (3513.5573 4055.084) (3514.1527 4059.8168)
      (3515.2214 4061.9084) (3517.4656 4061.1756) (3521.2214 4058.2595) (3526.2901 4054.3969) (3531.9237 4051.1145)
      (3537.0076 4049.6489) (3540.4275 4050.6718) (3541.4504 4054.0916) (3539.9847 4059.1756) (3536.7023 4064.8092)
      (3532.8397 4069.8779) (3529.9084 4073.6336) (3529.1756 4075.8779) (3531.2824 4076.9466) (3536.0153 4077.5267)
      (3542.3359 4078.3969) (3548.6412 4080.0611) (3553.2672 4082.6107) (3554.9618 4085.7557) (3553.2672 4088.9008)
      (3548.6412 4091.4504) (3542.3359 4093.1145) (3536.0153 4093.9695) (3531.2824 4094.5649) (3529.1756 4095.6336)
      (3529.9084 4097.8779) (3532.8397 4101.6336) (3536.7023 4106.7023) (3539.9847 4112.3359) (3541.4504 4117.4198)
      (3540.4275 4120.8397) (3537.0076 4121.8626) (3531.9237 4120.3969) (3526.2901 4117.1145) (3521.2214 4113.2519)
      (3517.4656 4110.3206) (3515.2214 4109.5878) (3514.1527 4111.6947) (3513.5573 4116.4275) (3512.7023 4122.7328)
      (3511.0382 4129.0382) (3508.4885 4133.6794) (3505.3435 4135.374) (3502.1985 4133.6794) (3499.6489 4129.0382)
      (3497.9847 4122.7328) (3497.1298 4116.4275) (3496.5344 4111.6947) (3495.4656 4109.5878) (3493.2214 4110.3206)
      (3489.4656 4113.2519) (3484.3969 4117.1145) (3478.7634 4120.3969) (3473.6794 4121.8626) (3470.2595 4120.8397)
      (3469.2366 4117.4198) (3470.7023 4112.3359) (3473.9847 4106.7023) (3477.8473 4101.6336) (3480.7786 4097.8779)
      (3481.5115 4095.6336) (3479.4046 4094.5649) (3474.6718 4093.9695) (3468.3511 4093.1145) (3462.0458 4091.4504)
      (3457.4198 4088.9008)
    ))
    ; P2531 -- see feature_dimensions_mm.csv
    ("06_ORNAMENT" 1 (
      (3480.916 6000.0) (3483.1603 5985.8473) (3489.6641 5973.084) (3499.8015 5962.9466) (3512.5649 5956.4427)
      (3526.7176 5954.1985) (3540.8702 5956.4427) (3553.6336 5962.9466) (3563.771 5973.084) (3570.2748 5985.8473)
      (3572.5191 6000.0) (3570.2748 6014.1527) (3563.771 6026.916) (3553.6336 6037.0534) (3540.8702 6043.5573)
      (3526.7176 6045.8015) (3512.5649 6043.5573) (3499.8015 6037.0534) (3489.6641 6026.916) (3483.1603 6014.1527)
    ))
    ; P2532 -- see feature_dimensions_mm.csv
    ("06_ORNAMENT" 1 (
      (3487.0229 5409.4198) (3505.3435 5388.8092) (3523.5267 5409.2519) (3520.5954 5410.9313) (3498.3664 5422.1679)
    ))
    ; P2533 -- see feature_dimensions_mm.csv
    ("06_ORNAMENT" 1 (
      (3487.0229 5097.9695) (3505.3435 5077.3588) (3523.6641 5097.9695) (3505.3435 5118.5802)
    ))
    ; P2534 -- see feature_dimensions_mm.csv
    ("06_ORNAMENT" 1 (
      (3487.0229 4786.5191) (3505.3435 4765.9084) (3523.6641 4786.5191) (3505.3435 4807.1298)
    ))
    ; P2535 -- see feature_dimensions_mm.csv
    ("06_ORNAMENT" 1 (
      (3487.0229 4163.6183) (3505.3435 4143.0076) (3523.6641 4163.6183) (3505.3435 4184.229)
    ))
    ; P2536 -- see feature_dimensions_mm.csv
    ("06_ORNAMENT" 1 (
      (3493.4351 5331.5573) (3494.3359 5326.9924) (3496.916 5323.1298) (3500.7939 5320.5496) (3505.3435 5319.6489)
      (3509.8931 5320.5496) (3513.771 5323.1298) (3516.3511 5326.9924) (3517.2519 5331.5573) (3516.3511 5336.1069)
      (3513.771 5339.9695) (3509.8931 5342.5496) (3505.3435 5343.4656) (3500.7939 5342.5496) (3496.916 5339.9695)
      (3494.3359 5336.1069)
    ))
    ; P2537 -- see feature_dimensions_mm.csv
    ("06_ORNAMENT" 1 (
      (3493.4351 5020.1069) (3494.3359 5015.542) (3496.916 5011.6794) (3500.7939 5009.0992) (3505.3435 5008.1985)
      (3509.8931 5009.0992) (3513.771 5011.6794) (3516.3511 5015.542) (3517.2519 5020.1069) (3516.3511 5024.6565)
      (3513.771 5028.5191) (3509.8931 5031.0992) (3505.3435 5032.0153) (3500.7939 5031.0992) (3496.916 5028.5191)
      (3494.3359 5024.6565)
    ))
    ; P2538 -- see feature_dimensions_mm.csv
    ("06_ORNAMENT" 1 (
      (3493.4351 4708.6565) (3494.3359 4704.0916) (3496.916 4700.229) (3500.7939 4697.6489) (3505.3435 4696.7481)
      (3509.8931 4697.6489) (3513.771 4700.229) (3516.3511 4704.0916) (3517.2519 4708.6565) (3516.3511 4713.2061)
      (3513.771 4717.0687) (3509.8931 4719.6489) (3505.3435 4720.5649) (3500.7939 4719.6489) (3496.916 4717.0687)
      (3494.3359 4713.2061)
    ))
    ; P2539 -- see feature_dimensions_mm.csv
    ("06_ORNAMENT" 1 (
      (3493.4351 4397.2061) (3494.3359 4392.6412) (3496.916 4388.7786) (3500.7939 4386.1985) (3505.3435 4385.2977)
      (3509.8931 4386.1985) (3513.771 4388.7786) (3516.3511 4392.6412) (3517.2519 4397.2061) (3516.3511 4401.7557)
      (3513.771 4405.6183) (3509.8931 4408.1985) (3505.3435 4409.1145) (3500.7939 4408.1985) (3496.916 4405.6183)
      (3494.3359 4401.7557)
    ))
    ; P2540 -- see feature_dimensions_mm.csv
    ("06_ORNAMENT" 1 (
      (3493.4351 4085.7557) (3494.3359 4081.1908) (3496.916 4077.3282) (3500.7939 4074.7481) (3505.3435 4073.8473)
      (3509.8931 4074.7481) (3513.771 4077.3282) (3516.3511 4081.1908) (3517.2519 4085.7557) (3516.3511 4090.3053)
      (3513.771 4094.1679) (3509.8931 4096.7481) (3505.3435 4097.6641) (3500.7939 4096.7481) (3496.916 4094.1679)
      (3494.3359 4090.3053)
    ))
    ; P2541 -- see feature_dimensions_mm.csv
    ("06_ORNAMENT" 1 (
      (3500.8244 5900.4885) (3508.8092 5909.9542) (3516.1374 5919.5878) (3521.8779 5926.1985) (3526.7176 5928.5496)
      (3531.5573 5926.1985) (3537.2977 5919.5878) (3544.626 5909.9542) (3549.9389 5903.6489) (3545.6183 5903.8015)
      (3523.2519 5903.0229) (3501.0534 5900.5191)
    ))
    ; P2542 -- see feature_dimensions_mm.csv
    ("06_ORNAMENT" 1 (
      (3533.5878 5175.8321) (3535.2824 5172.687) (3539.9084 5170.1374) (3546.2137 5168.4733) (3552.5344 5167.6031)
      (3557.2672 5167.0229) (3559.374 5165.9542) (3558.6412 5163.7099) (3555.7099 5159.9542) (3551.8473 5154.8855)
      (3548.5649 5149.2519) (3547.0992 5144.1679) (3548.1221 5140.7481) (3551.542 5139.7252) (3556.626 5141.1908)
      (3562.2595 5144.4733) (3567.3282 5148.3206) (3571.084 5151.2519) (3573.3282 5151.9847) (3574.3969 5149.8931)
      (3574.9924 5145.1603) (3575.8473 5138.8397) (3577.5115 5132.5344) (3580.0611 5127.9084) (3583.2061 5126.2137)
      (3586.3511 5127.9084) (3588.9008 5132.5344) (3590.5649 5138.8397) (3591.4198 5145.1603) (3592.0153 5149.8931)
      (3593.084 5151.9847) (3595.3282 5151.2519) (3599.084 5148.3206) (3604.1527 5144.4733) (3609.7863 5141.1908)
      (3614.8702 5139.7252) (3618.2901 5140.7481) (3619.313 5144.1679) (3617.8473 5149.2519) (3614.5649 5154.8855)
      (3610.7023 5159.9542) (3607.771 5163.7099) (3607.0382 5165.9542) (3609.145 5167.0229) (3613.8779 5167.6031)
      (3620.1985 5168.4733) (3626.5038 5170.1374) (3631.1298 5172.687) (3632.8244 5175.8321) (3631.1298 5178.9771)
      (3626.5038 5181.5267) (3620.1985 5183.1908) (3613.8779 5184.0458) (3609.145 5184.6412) (3607.0382 5185.7099)
      (3607.771 5187.9542) (3610.7023 5191.7099) (3614.5649 5196.7786) (3617.8473 5202.4122) (3619.313 5207.4962)
      (3618.2901 5210.916) (3614.8702 5211.9389) (3609.7863 5210.4733) (3604.1527 5207.1908) (3599.084 5203.3282)
      (3595.3282 5200.3969) (3593.084 5199.6641) (3592.0153 5201.771) (3591.4198 5206.5038) (3590.5649 5212.8092)
      (3588.9008 5219.1145) (3586.3511 5223.7557) (3583.2061 5225.4504) (3580.0611 5223.7557) (3577.5115 5219.1145)
      (3575.8473 5212.8092) (3574.9924 5206.5038) (3574.3969 5201.771) (3573.3282 5199.6641) (3571.084 5200.3969)
      (3567.3282 5203.3282) (3562.2595 5207.1908) (3556.626 5210.4733) (3551.542 5211.9389) (3548.1221 5210.916)
      (3547.0992 5207.4962) (3548.5649 5202.4122) (3551.8473 5196.7786) (3555.7099 5191.7099) (3558.6412 5187.9542)
      (3559.374 5185.7099) (3557.2672 5184.6412) (3552.5344 5184.0458) (3546.2137 5183.1908) (3539.9084 5181.5267)
      (3535.2824 5178.9771)
    ))
    ; P2543 -- see feature_dimensions_mm.csv
    ("06_ORNAMENT" 1 (
      (3533.5878 4864.3817) (3535.2824 4861.2366) (3539.9084 4858.687) (3546.2137 4857.0229) (3552.5344 4856.1527)
      (3557.2672 4855.5725) (3559.374 4854.5038) (3558.6412 4852.2595) (3555.7099 4848.5038) (3551.8473 4843.4351)
      (3548.5649 4837.8015) (3547.0992 4832.7176) (3548.1221 4829.2977) (3551.542 4828.2748) (3556.626 4829.7405)
      (3562.2595 4833.0229) (3567.3282 4836.8702) (3571.084 4839.8015) (3573.3282 4840.5344) (3574.3969 4838.4427)
      (3574.9924 4833.7099) (3575.8473 4827.3893) (3577.5115 4821.084) (3580.0611 4816.458) (3583.2061 4814.7634)
      (3586.3511 4816.458) (3588.9008 4821.084) (3590.5649 4827.3893) (3591.4198 4833.7099) (3592.0153 4838.4427)
      (3593.084 4840.5344) (3595.3282 4839.8015) (3599.084 4836.8702) (3604.1527 4833.0229) (3609.7863 4829.7405)
      (3614.8702 4828.2748) (3618.2901 4829.2977) (3619.313 4832.7176) (3617.8473 4837.8015) (3614.5649 4843.4351)
      (3610.7023 4848.5038) (3607.771 4852.2595) (3607.0382 4854.5038) (3609.145 4855.5725) (3613.8779 4856.1527)
      (3620.1985 4857.0229) (3626.5038 4858.687) (3631.1298 4861.2366) (3632.8244 4864.3817) (3631.1298 4867.5267)
      (3626.5038 4870.0763) (3620.1985 4871.7405) (3613.8779 4872.5954) (3609.145 4873.1908) (3607.0382 4874.2595)
      (3607.771 4876.5038) (3610.7023 4880.2595) (3614.5649 4885.3282) (3617.8473 4890.9618) (3619.313 4896.0458)
      (3618.2901 4899.4656) (3614.8702 4900.4885) (3609.7863 4899.0229) (3604.1527 4895.7405) (3599.084 4891.8779)
      (3595.3282 4888.9466) (3593.084 4888.2137) (3592.0153 4890.3206) (3591.4198 4895.0534) (3590.5649 4901.3588)
      (3588.9008 4907.6641) (3586.3511 4912.3053) (3583.2061 4914.0) (3580.0611 4912.3053) (3577.5115 4907.6641)
      (3575.8473 4901.3588) (3574.9924 4895.0534) (3574.3969 4890.3206) (3573.3282 4888.2137) (3571.084 4888.9466)
      (3567.3282 4891.8779) (3562.2595 4895.7405) (3556.626 4899.0229) (3551.542 4900.4885) (3548.1221 4899.4656)
      (3547.0992 4896.0458) (3548.5649 4890.9618) (3551.8473 4885.3282) (3555.7099 4880.2595) (3558.6412 4876.5038)
      (3559.374 4874.2595) (3557.2672 4873.1908) (3552.5344 4872.5954) (3546.2137 4871.7405) (3539.9084 4870.0763)
      (3535.2824 4867.5267)
    ))
    ; P2544 -- see feature_dimensions_mm.csv
    ("06_ORNAMENT" 1 (
      (3533.5878 4552.9313) (3535.2824 4549.7863) (3539.9084 4547.2366) (3546.2137 4545.5725) (3552.5344 4544.7023)
      (3557.2672 4544.1221) (3559.374 4543.0534) (3558.6412 4540.8092) (3555.7099 4537.0534) (3551.8473 4531.9847)
      (3548.5649 4526.3511) (3547.0992 4521.2672) (3548.1221 4517.8473) (3551.542 4516.8244) (3556.626 4518.2901)
      (3562.2595 4521.5725) (3567.3282 4525.4198) (3571.084 4528.3511) (3573.3282 4529.084) (3574.3969 4526.9924)
      (3574.9924 4522.2595) (3575.8473 4515.9389) (3577.5115 4509.6336) (3580.0611 4505.0076) (3583.2061 4503.313)
      (3586.3511 4505.0076) (3588.9008 4509.6336) (3590.5649 4515.9389) (3591.4198 4522.2595) (3592.0153 4526.9924)
      (3593.084 4529.084) (3595.3282 4528.3511) (3599.084 4525.4198) (3604.1527 4521.5725) (3609.7863 4518.2901)
      (3614.8702 4516.8244) (3618.2901 4517.8473) (3619.313 4521.2672) (3617.8473 4526.3511) (3614.5649 4531.9847)
      (3610.7023 4537.0534) (3607.771 4540.8092) (3607.0382 4543.0534) (3609.145 4544.1221) (3613.8779 4544.7023)
      (3620.1985 4545.5725) (3626.5038 4547.2366) (3631.1298 4549.7863) (3632.8244 4552.9313) (3631.1298 4556.0763)
      (3626.5038 4558.626) (3620.1985 4560.2901) (3613.8779 4561.145) (3609.145 4561.7405) (3607.0382 4562.8092)
      (3607.771 4565.0534) (3610.7023 4568.8092) (3614.5649 4573.8779) (3617.8473 4579.5115) (3619.313 4584.5954)
      (3618.2901 4588.0153) (3614.8702 4589.0382) (3609.7863 4587.5725) (3604.1527 4584.2901) (3599.084 4580.4275)
      (3595.3282 4577.4962) (3593.084 4576.7634) (3592.0153 4578.8702) (3591.4198 4583.6031) (3590.5649 4589.9084)
      (3588.9008 4596.2137) (3586.3511 4600.855) (3583.2061 4602.5496) (3580.0611 4600.855) (3577.5115 4596.2137)
      (3575.8473 4589.9084) (3574.9924 4583.6031) (3574.3969 4578.8702) (3573.3282 4576.7634) (3571.084 4577.4962)
      (3567.3282 4580.4275) (3562.2595 4584.2901) (3556.626 4587.5725) (3551.542 4589.0382) (3548.1221 4588.0153)
      (3547.0992 4584.5954) (3548.5649 4579.5115) (3551.8473 4573.8779) (3555.7099 4568.8092) (3558.6412 4565.0534)
      (3559.374 4562.8092) (3557.2672 4561.7405) (3552.5344 4561.145) (3546.2137 4560.2901) (3539.9084 4558.626)
      (3535.2824 4556.0763)
    ))
    ; P2545 -- see feature_dimensions_mm.csv
    ("06_ORNAMENT" 1 (
      (3533.5878 4241.4809) (3535.2824 4238.3359) (3539.9084 4235.7863) (3546.2137 4234.1221) (3552.5344 4233.2519)
      (3557.2672 4232.6718) (3559.374 4231.6031) (3558.6412 4229.3588) (3555.7099 4225.6031) (3551.8473 4220.5344)
      (3548.5649 4214.9008) (3547.0992 4209.8168) (3548.1221 4206.3969) (3551.542 4205.374) (3556.626 4206.8397)
      (3562.2595 4210.1221) (3567.3282 4213.9695) (3571.084 4216.9008) (3573.3282 4217.6336) (3574.3969 4215.542)
      (3574.9924 4210.8092) (3575.8473 4204.4885) (3577.5115 4198.1832) (3580.0611 4193.5573) (3583.2061 4191.8626)
      (3586.3511 4193.5573) (3588.9008 4198.1832) (3590.5649 4204.4885) (3591.4198 4210.8092) (3592.0153 4215.542)
      (3593.084 4217.6336) (3595.3282 4216.9008) (3599.084 4213.9695) (3604.1527 4210.1221) (3609.7863 4206.8397)
      (3614.8702 4205.374) (3618.2901 4206.3969) (3619.313 4209.8168) (3617.8473 4214.9008) (3614.5649 4220.5344)
      (3610.7023 4225.6031) (3607.771 4229.3588) (3607.0382 4231.6031) (3609.145 4232.6718) (3613.8779 4233.2519)
      (3620.1985 4234.1221) (3626.5038 4235.7863) (3631.1298 4238.3359) (3632.8244 4241.4809) (3631.1298 4244.626)
      (3626.5038 4247.1756) (3620.1985 4248.8397) (3613.8779 4249.6947) (3609.145 4250.2901) (3607.0382 4251.3588)
      (3607.771 4253.6031) (3610.7023 4257.3588) (3614.5649 4262.4275) (3617.8473 4268.0611) (3619.313 4273.145)
      (3618.2901 4276.5649) (3614.8702 4277.5878) (3609.7863 4276.1221) (3604.1527 4272.8397) (3599.084 4268.9771)
      (3595.3282 4266.0458) (3593.084 4265.313) (3592.0153 4267.4198) (3591.4198 4272.1527) (3590.5649 4278.458)
      (3588.9008 4284.7634) (3586.3511 4289.4046) (3583.2061 4291.0992) (3580.0611 4289.4046) (3577.5115 4284.7634)
      (3575.8473 4278.458) (3574.9924 4272.1527) (3574.3969 4267.4198) (3573.3282 4265.313) (3571.084 4266.0458)
      (3567.3282 4268.9771) (3562.2595 4272.8397) (3556.626 4276.1221) (3551.542 4277.5878) (3548.1221 4276.5649)
      (3547.0992 4273.145) (3548.5649 4268.0611) (3551.8473 4262.4275) (3555.7099 4257.3588) (3558.6412 4253.6031)
      (3559.374 4251.3588) (3557.2672 4250.2901) (3552.5344 4249.6947) (3546.2137 4248.8397) (3539.9084 4247.1756)
      (3535.2824 4244.626)
    ))
    ; P2546 -- see feature_dimensions_mm.csv
    ("06_ORNAMENT" 1 (
      (3533.5878 3930.0305) (3535.2824 3926.8855) (3539.9084 3924.3359) (3546.2137 3922.6718) (3552.5344 3921.8015)
      (3557.2672 3921.2214) (3559.374 3920.1527) (3558.6412 3917.9084) (3555.7099 3914.1527) (3551.8473 3909.084)
      (3548.5649 3903.4504) (3547.0992 3898.3664) (3548.1221 3894.9466) (3551.542 3893.9237) (3556.626 3895.3893)
      (3562.2595 3898.6718) (3567.3282 3902.5191) (3571.084 3905.4504) (3573.3282 3906.1832) (3574.3969 3904.0916)
      (3574.9924 3899.3588) (3575.8473 3893.0382) (3577.5115 3886.7328) (3580.0611 3882.1069) (3583.2061 3880.4122)
      (3586.3511 3882.1069) (3588.9008 3886.7328) (3590.5649 3893.0382) (3591.4198 3899.3588) (3592.0153 3904.0916)
      (3593.084 3906.1832) (3595.3282 3905.4504) (3599.084 3902.5191) (3604.1527 3898.6718) (3609.7863 3895.3893)
      (3614.8702 3893.9237) (3618.2901 3894.9466) (3619.313 3898.3664) (3617.8473 3903.4504) (3614.5649 3909.084)
      (3610.7023 3914.1527) (3607.771 3917.9084) (3607.0382 3920.1527) (3609.145 3921.2214) (3613.8779 3921.8015)
      (3620.1985 3922.6718) (3626.5038 3924.3359) (3631.1298 3926.8855) (3632.8244 3930.0305) (3631.1298 3933.1756)
      (3626.5038 3935.7252) (3620.1985 3937.3893) (3613.8779 3938.2443) (3609.145 3938.8397) (3607.0382 3939.9084)
      (3607.771 3942.1527) (3610.7023 3945.9084) (3614.5649 3950.9771) (3617.8473 3956.6107) (3619.313 3961.6947)
      (3618.2901 3965.1145) (3614.8702 3966.1374) (3609.7863 3964.6718) (3604.1527 3961.3893) (3599.084 3957.5267)
      (3595.3282 3954.5954) (3593.084 3953.8626) (3592.0153 3955.9695) (3591.4198 3960.7023) (3590.5649 3967.0076)
      (3588.9008 3973.313) (3586.3511 3977.9542) (3583.2061 3979.6489) (3580.0611 3977.9542) (3577.5115 3973.313)
      (3575.8473 3967.0076) (3574.9924 3960.7023) (3574.3969 3955.9695) (3573.3282 3953.8626) (3571.084 3954.5954)
      (3567.3282 3957.5267) (3562.2595 3961.3893) (3556.626 3964.6718) (3551.542 3966.1374) (3548.1221 3965.1145)
      (3547.0992 3961.6947) (3548.5649 3956.6107) (3551.8473 3950.9771) (3555.7099 3945.9084) (3558.6412 3942.1527)
      (3559.374 3939.9084) (3557.2672 3938.8397) (3552.5344 3938.2443) (3546.2137 3937.3893) (3539.9084 3935.7252)
      (3535.2824 3933.1756)
    ))
    ; P2547 -- see feature_dimensions_mm.csv
    ("06_ORNAMENT" 1 (
      (3564.8855 5253.6947) (3583.2061 5233.084) (3601.5267 5253.6947) (3583.2061 5274.3053)
    ))
    ; P2548 -- see feature_dimensions_mm.csv
    ("06_ORNAMENT" 1 (
      (3564.8855 4942.2443) (3583.2061 4921.6336) (3601.5267 4942.2443) (3583.2061 4962.855)
    ))
    ; P2549 -- see feature_dimensions_mm.csv
    ("06_ORNAMENT" 1 (
      (3564.8855 4630.7939) (3583.2061 4610.1832) (3601.5267 4630.7939) (3583.2061 4651.4046)
    ))
    ; P2550 -- see feature_dimensions_mm.csv
    ("06_ORNAMENT" 1 (
      (3564.8855 4319.3435) (3583.2061 4298.7328) (3601.5267 4319.3435) (3583.2061 4339.9542)
    ))
    ; P2551 -- see feature_dimensions_mm.csv
    ("06_ORNAMENT" 1 (
      (3564.8855 4007.8931) (3583.2061 3987.2824) (3601.5267 4007.8931) (3583.2061 4028.5038)
    ))
    ; P2552 -- see feature_dimensions_mm.csv
    ("06_ORNAMENT" 1 (
      (3571.2977 5175.8321) (3572.1985 5171.2672) (3574.7786 5167.4046) (3578.6565 5164.8244) (3583.2061 5163.9237)
      (3587.7557 5164.8244) (3591.6336 5167.4046) (3594.2137 5171.2672) (3595.1145 5175.8321) (3594.2137 5180.3817)
      (3591.6336 5184.2443) (3587.7557 5186.8244) (3583.2061 5187.7405) (3578.6565 5186.8244) (3574.7786 5184.2443)
      (3572.1985 5180.3817)
    ))
    ; P2553 -- see feature_dimensions_mm.csv
    ("06_ORNAMENT" 1 (
      (3571.2977 4864.3817) (3572.1985 4859.8168) (3574.7786 4855.9542) (3578.6565 4853.374) (3583.2061 4852.4733)
      (3587.7557 4853.374) (3591.6336 4855.9542) (3594.2137 4859.8168) (3595.1145 4864.3817) (3594.2137 4868.9313)
      (3591.6336 4872.7939) (3587.7557 4875.374) (3583.2061 4876.2901) (3578.6565 4875.374) (3574.7786 4872.7939)
      (3572.1985 4868.9313)
    ))
    ; P2554 -- see feature_dimensions_mm.csv
    ("06_ORNAMENT" 1 (
      (3571.2977 4552.9313) (3572.1985 4548.3664) (3574.7786 4544.5038) (3578.6565 4541.9237) (3583.2061 4541.0229)
      (3587.7557 4541.9237) (3591.6336 4544.5038) (3594.2137 4548.3664) (3595.1145 4552.9313) (3594.2137 4557.4809)
      (3591.6336 4561.3435) (3587.7557 4563.9237) (3583.2061 4564.8397) (3578.6565 4563.9237) (3574.7786 4561.3435)
      (3572.1985 4557.4809)
    ))
    ; P2555 -- see feature_dimensions_mm.csv
    ("06_ORNAMENT" 1 (
      (3571.2977 4241.4809) (3572.1985 4236.916) (3574.7786 4233.0534) (3578.6565 4230.4733) (3583.2061 4229.5725)
      (3587.7557 4230.4733) (3591.6336 4233.0534) (3594.2137 4236.916) (3595.1145 4241.4809) (3594.2137 4246.0305)
      (3591.6336 4249.8931) (3587.7557 4252.4733) (3583.2061 4253.3893) (3578.6565 4252.4733) (3574.7786 4249.8931)
      (3572.1985 4246.0305)
    ))
    ; P2556 -- see feature_dimensions_mm.csv
    ("06_ORNAMENT" 1 (
      (3571.2977 3930.0305) (3572.1985 3925.4656) (3574.7786 3921.6031) (3578.6565 3919.0229) (3583.2061 3918.1221)
      (3587.7557 3919.0229) (3591.6336 3921.6031) (3594.2137 3925.4656) (3595.1145 3930.0305) (3594.2137 3934.5802)
      (3591.6336 3938.4427) (3587.7557 3941.0229) (3583.2061 3941.9389) (3578.6565 3941.0229) (3574.7786 3938.4427)
      (3572.1985 3934.5802)
    ))
    ; P2557 -- see feature_dimensions_mm.csv
    ("06_ORNAMENT" 1 (
      (3601.0229 5705.9084) (3601.8931 5697.2977) (3605.7099 5695.8931) (3607.145 5695.3282) (3654.6107 5675.9542)
      (3656.2748 5675.2366) (3699.4962 5655.5725) (3696.1221 5662.3664) (3684.6412 5681.3282) (3671.6641 5698.9313)
      (3657.1756 5714.8397) (3656.0 5715.8779) (3659.8931 5714.0) (3680.9313 5706.6565) (3702.7786 5701.3435)
      (3725.145 5697.9542) (3747.6794 5696.4122) (3770.1069 5696.5802) (3792.0916 5698.3664) (3813.313 5701.6641)
      (3833.4656 5706.3817) (3852.229 5712.3817) (3869.2824 5719.5878) (3884.3206 5727.8931) (3869.0992 5738.5038)
      (3852.0305 5748.3359) (3833.4046 5757.2214) (3813.4962 5765.0076) (3792.5954 5771.542) (3770.9466 5776.6718)
      (3748.855 5780.2595) (3726.5954 5782.1527) (3704.4275 5782.1985) (3682.6565 5780.229) (3661.5267 5776.1221)
      (3641.3435 5769.6947) (3622.3664 5760.8244) (3604.8855 5749.3435) (3601.4962 5727.771)
    ))
    ; P2558 -- see feature_dimensions_mm.csv
    ("06_ORNAMENT" 1 (
      (3611.4504 5020.1069) (3613.145 5016.9618) (3617.771 5014.4122) (3624.0763 5012.7481) (3630.3969 5011.8779)
      (3635.1298 5011.2977) (3637.2366 5010.229) (3636.5038 5007.9847) (3633.5725 5004.229) (3629.7099 4999.1603)
      (3626.4275 4993.5267) (3624.9618 4988.4427) (3625.9847 4985.0229) (3629.4046 4984.0) (3634.4885 4985.4656)
      (3640.1221 4988.7481) (3645.1908 4992.5954) (3648.9466 4995.5267) (3651.1908 4996.2595) (3652.2595 4994.1679)
      (3652.855 4989.4351) (3653.7099 4983.1145) (3655.374 4976.8092) (3657.9237 4972.1832) (3661.0687 4970.4885)
      (3664.2137 4972.1832) (3666.7634 4976.8092) (3668.4275 4983.1145) (3669.2824 4989.4351) (3669.8779 4994.1679)
      (3670.9466 4996.2595) (3673.1908 4995.5267) (3676.9466 4992.5954) (3682.0153 4988.7481) (3687.6489 4985.4656)
      (3692.7328 4984.0) (3694.6565 4984.5649) (3694.6565 4995.3282) (3692.4275 4999.1603) (3688.5649 5004.229)
      (3685.6336 5007.9847) (3684.9008 5010.229) (3687.0076 5011.2977) (3691.7405 5011.8779) (3694.6565 5012.2901)
      (3694.6565 5027.9237) (3691.7405 5028.3206) (3687.0076 5028.916) (3684.9008 5029.9847) (3685.6336 5032.229)
      (3688.5649 5035.9847) (3692.4275 5041.0534) (3694.6565 5044.8855) (3694.6565 5055.6336) (3692.7328 5056.2137)
      (3687.6489 5054.7481) (3682.0153 5051.4656) (3676.9466 5047.6031) (3673.1908 5044.6718) (3670.9466 5043.9389)
      (3669.8779 5046.0458) (3669.2824 5050.7786) (3668.4275 5057.084) (3666.7634 5063.3893) (3664.2137 5068.0305)
      (3661.0687 5069.7252) (3657.9237 5068.0305) (3655.374 5063.3893) (3653.7099 5057.084) (3652.855 5050.7786)
      (3652.2595 5046.0458) (3651.1908 5043.9389) (3648.9466 5044.6718) (3645.1908 5047.6031) (3640.1221 5051.4656)
      (3634.4885 5054.7481) (3629.4046 5056.2137) (3625.9847 5055.1908) (3624.9618 5051.771) (3626.4275 5046.687)
      (3629.7099 5041.0534) (3633.5725 5035.9847) (3636.5038 5032.229) (3637.2366 5029.9847) (3635.1298 5028.916)
      (3630.3969 5028.3206) (3624.0763 5027.4656) (3617.771 5025.8015) (3613.145 5023.2519)
    ))
    ; P2559 -- see feature_dimensions_mm.csv
    ("06_ORNAMENT" 1 (
      (3611.4504 4708.6565) (3613.145 4705.5115) (3617.771 4702.9618) (3624.0763 4701.2977) (3630.3969 4700.4275)
      (3635.1298 4699.8473) (3637.2366 4698.7786) (3636.5038 4696.5344) (3633.5725 4692.7786) (3629.7099 4687.7099)
      (3626.4275 4682.0763) (3624.9618 4676.9924) (3625.9847 4673.5725) (3629.4046 4672.5496) (3634.4885 4674.0153)
      (3640.1221 4677.2977) (3645.1908 4681.145) (3648.9466 4684.0763) (3651.1908 4684.8092) (3652.2595 4682.7176)
      (3652.855 4677.9847) (3653.7099 4671.6641) (3655.374 4665.3588) (3657.9237 4660.7328) (3661.0687 4659.0382)
      (3664.2137 4660.7328) (3666.7634 4665.3588) (3668.4275 4671.6641) (3669.2824 4677.9847) (3669.8779 4682.7176)
      (3670.9466 4684.8092) (3673.1908 4684.0763) (3676.9466 4681.145) (3682.0153 4677.2977) (3687.6489 4674.0153)
      (3692.7328 4672.5496) (3694.6565 4673.1145) (3694.6565 4683.8779) (3692.4275 4687.7099) (3688.5649 4692.7786)
      (3685.6336 4696.5344) (3684.9008 4698.7786) (3687.0076 4699.8473) (3691.7405 4700.4275) (3694.6565 4700.8397)
      (3694.6565 4716.4733) (3691.7405 4716.8702) (3687.0076 4717.4656) (3684.9008 4718.5344) (3685.6336 4720.7786)
      (3688.5649 4724.5344) (3692.4275 4729.6031) (3694.6565 4733.4351) (3694.6565 4744.1832) (3692.7328 4744.7634)
      (3687.6489 4743.2977) (3682.0153 4740.0153) (3676.9466 4736.1527) (3673.1908 4733.2214) (3670.9466 4732.4885)
      (3669.8779 4734.5954) (3669.2824 4739.3282) (3668.4275 4745.6336) (3666.7634 4751.9389) (3664.2137 4756.5802)
      (3661.0687 4758.2748) (3657.9237 4756.5802) (3655.374 4751.9389) (3653.7099 4745.6336) (3652.855 4739.3282)
      (3652.2595 4734.5954) (3651.1908 4732.4885) (3648.9466 4733.2214) (3645.1908 4736.1527) (3640.1221 4740.0153)
      (3634.4885 4743.2977) (3629.4046 4744.7634) (3625.9847 4743.7405) (3624.9618 4740.3206) (3626.4275 4735.2366)
      (3629.7099 4729.6031) (3633.5725 4724.5344) (3636.5038 4720.7786) (3637.2366 4718.5344) (3635.1298 4717.4656)
      (3630.3969 4716.8702) (3624.0763 4716.0153) (3617.771 4714.3511) (3613.145 4711.8015)
    ))
    ; P2560 -- see feature_dimensions_mm.csv
    ("06_ORNAMENT" 1 (
      (3611.4504 4397.2061) (3613.145 4394.0611) (3617.771 4391.5115) (3624.0763 4389.8473) (3630.3969 4388.9771)
      (3635.1298 4388.3969) (3637.2366 4387.3282) (3636.5038 4385.084) (3633.5725 4381.3282) (3629.7099 4376.2595)
      (3626.4275 4370.626) (3624.9618 4365.542) (3625.9847 4362.1221) (3629.4046 4361.0992) (3634.4885 4362.5649)
      (3640.1221 4365.8473) (3645.1908 4369.6947) (3648.9466 4372.626) (3651.1908 4373.3588) (3652.2595 4371.2672)
      (3652.855 4366.5344) (3653.7099 4360.2137) (3655.374 4353.9084) (3657.9237 4349.2824) (3661.0687 4347.5878)
      (3664.2137 4349.2824) (3666.7634 4353.9084) (3668.4275 4360.2137) (3669.2824 4366.5344) (3669.8779 4371.2672)
      (3670.9466 4373.3588) (3673.1908 4372.626) (3676.9466 4369.6947) (3682.0153 4365.8473) (3687.6489 4362.5649)
      (3692.7328 4361.0992) (3694.6565 4361.6641) (3694.6565 4372.4275) (3692.4275 4376.2595) (3688.5649 4381.3282)
      (3685.6336 4385.084) (3684.9008 4387.3282) (3687.0076 4388.3969) (3691.7405 4388.9771) (3694.6565 4389.3893)
      (3694.6565 4405.0229) (3691.7405 4405.4198) (3687.0076 4406.0153) (3684.9008 4407.084) (3685.6336 4409.3282)
      (3687.8931 4412.2137) (3634.2443 4412.2137) (3636.5038 4409.3282) (3637.2366 4407.084) (3635.1298 4406.0153)
      (3630.3969 4405.4198) (3624.0763 4404.5649) (3617.771 4402.9008) (3613.145 4400.3511)
    ))
    ; P2561 -- see feature_dimensions_mm.csv
    ("06_ORNAMENT" 1 (
      (3611.4504 4085.7557) (3613.145 4082.6107) (3617.771 4080.0611) (3624.0763 4078.3969) (3630.3969 4077.5267)
      (3635.1298 4076.9466) (3637.2366 4075.8779) (3636.5038 4073.6336) (3633.5725 4069.8779) (3629.7099 4064.8092)
      (3626.4275 4059.1756) (3624.9618 4054.0916) (3625.9847 4050.6718) (3629.4046 4049.6489) (3634.4885 4051.1145)
      (3640.1221 4054.3969) (3645.1908 4058.2595) (3648.9466 4061.1756) (3651.1908 4061.9084) (3652.2595 4059.8168)
      (3652.855 4055.084) (3653.7099 4048.7634) (3655.374 4042.458) (3657.9237 4037.8321) (3661.0687 4036.1374)
      (3664.2137 4037.8321) (3666.7634 4042.458) (3668.4275 4048.7634) (3669.2824 4055.084) (3669.8779 4059.8168)
      (3670.9466 4061.9084) (3673.1908 4061.1756) (3676.9466 4058.2595) (3682.0153 4054.3969) (3687.6489 4051.1145)
      (3692.7328 4049.6489) (3694.6565 4050.2137) (3694.6565 4060.9771) (3692.4275 4064.8092) (3688.5649 4069.8779)
      (3685.6336 4073.6336) (3684.9008 4075.8779) (3687.0076 4076.9466) (3691.7405 4077.5267) (3694.6565 4077.9389)
      (3694.6565 4093.5725) (3691.7405 4093.9695) (3687.0076 4094.5649) (3684.9008 4095.6336) (3685.6336 4097.8779)
      (3688.5649 4101.6336) (3692.4275 4106.7023) (3694.6565 4110.5344) (3694.6565 4121.2824) (3692.7328 4121.8626)
      (3687.6489 4120.3969) (3682.0153 4117.1145) (3676.9466 4113.2519) (3673.1908 4110.3206) (3670.9466 4109.5878)
      (3669.8779 4111.6947) (3669.2824 4116.4275) (3668.4275 4122.7328) (3666.7634 4129.0382) (3664.2137 4133.6794)
      (3661.0687 4135.374) (3657.9237 4133.6794) (3655.374 4129.0382) (3653.7099 4122.7328) (3652.855 4116.4275)
      (3652.2595 4111.6947) (3651.1908 4109.5878) (3648.9466 4110.3206) (3645.1908 4113.2519) (3640.1221 4117.1145)
      (3634.4885 4120.3969) (3629.4046 4121.8626) (3625.9847 4120.8397) (3624.9618 4117.4198) (3626.4275 4112.3359)
      (3629.7099 4106.7023) (3633.5725 4101.6336) (3636.5038 4097.8779) (3637.2366 4095.6336) (3635.1298 4094.5649)
      (3630.3969 4093.9695) (3624.0763 4093.1145) (3617.771 4091.4504) (3613.145 4088.9008)
    ))
    ; P2562 -- see feature_dimensions_mm.csv
    ("06_ORNAMENT" 1 (
      (3642.7481 5097.9695) (3661.0687 5077.3588) (3679.3893 5097.9695) (3661.0687 5118.5802)
    ))
    ; P2563 -- see feature_dimensions_mm.csv
    ("06_ORNAMENT" 1 (
      (3642.7481 4786.5191) (3661.0687 4765.9084) (3679.3893 4786.5191) (3661.0687 4807.1298)
    ))
    ; P2564 -- see feature_dimensions_mm.csv
    ("06_ORNAMENT" 1 (
      (3642.7481 4163.6183) (3661.0687 4143.0076) (3679.3893 4163.6183) (3661.0687 4184.229)
    ))
    ; P2565 -- see feature_dimensions_mm.csv
    ("06_ORNAMENT" 1 (
      (3642.7481 3852.1679) (3660.626 3832.0611) (3661.5115 3832.0611) (3679.3893 3852.1679) (3661.0687 3872.7786)
    ))
    ; P2566 -- see feature_dimensions_mm.csv
    ("06_ORNAMENT" 1 (
      (3648.855 7374.0458) (3709.9237 7343.5115) (3770.9924 7374.0458) (3709.9237 7404.5802)
    ))
    ; P2567 -- see feature_dimensions_mm.csv
    ("06_ORNAMENT" 1 (
      (3648.855 7282.4427) (3709.9237 7251.9084) (3770.9924 7282.4427) (3709.9237 7312.9771)
    ))
    ; P2568 -- see feature_dimensions_mm.csv
    ("06_ORNAMENT" 1 (
      (3648.855 7190.8397) (3709.9237 7160.3053) (3770.9924 7190.8397) (3709.9237 7221.374)
    ))
    ; P2569 -- see feature_dimensions_mm.csv
    ("06_ORNAMENT" 1 (
      (3649.1603 5020.1069) (3650.0611 5015.542) (3652.6412 5011.6794) (3656.5191 5009.0992) (3661.0687 5008.1985)
      (3665.6183 5009.0992) (3669.4962 5011.6794) (3672.0763 5015.542) (3672.9771 5020.1069) (3672.0763 5024.6565)
      (3669.4962 5028.5191) (3665.6183 5031.0992) (3661.0687 5032.0153) (3656.5191 5031.0992) (3652.6412 5028.5191)
      (3650.0611 5024.6565)
    ))
    ; P2570 -- see feature_dimensions_mm.csv
    ("06_ORNAMENT" 1 (
      (3649.1603 4708.6565) (3650.0611 4704.0916) (3652.6412 4700.229) (3656.5191 4697.6489) (3661.0687 4696.7481)
      (3665.6183 4697.6489) (3669.4962 4700.229) (3672.0763 4704.0916) (3672.9771 4708.6565) (3672.0763 4713.2061)
      (3669.4962 4717.0687) (3665.6183 4719.6489) (3661.0687 4720.5649) (3656.5191 4719.6489) (3652.6412 4717.0687)
      (3650.0611 4713.2061)
    ))
    ; P2571 -- see feature_dimensions_mm.csv
    ("06_ORNAMENT" 1 (
      (3649.1603 4397.2061) (3650.0611 4392.6412) (3652.6412 4388.7786) (3656.5191 4386.1985) (3661.0687 4385.2977)
      (3665.6183 4386.1985) (3669.4962 4388.7786) (3672.0763 4392.6412) (3672.9771 4397.2061) (3672.0763 4401.7557)
      (3669.4962 4405.6183) (3665.6183 4408.1985) (3661.0687 4409.1145) (3656.5191 4408.1985) (3652.6412 4405.6183)
      (3650.0611 4401.7557)
    ))
    ; P2572 -- see feature_dimensions_mm.csv
    ("06_ORNAMENT" 1 (
      (3649.1603 4085.7557) (3650.0611 4081.1908) (3652.6412 4077.3282) (3656.5191 4074.7481) (3661.0687 4073.8473)
      (3665.6183 4074.7481) (3669.4962 4077.3282) (3672.0763 4081.1908) (3672.9771 4085.7557) (3672.0763 4090.3053)
      (3669.4962 4094.1679) (3665.6183 4096.7481) (3661.0687 4097.6641) (3656.5191 4096.7481) (3652.6412 4094.1679)
      (3650.0611 4090.3053)
    ))
    ; P2573 -- see feature_dimensions_mm.csv
    ("06_ORNAMENT" 1 (
      (3664.1221 3007.6336) (3694.6565 2977.0992) (3725.1908 3007.6336) (3694.6565 3038.1679)
    ))
    ; P2574 -- see feature_dimensions_mm.csv
    ("06_ORNAMENT" 1 (
      (3664.1221 2916.0305) (3694.6565 2885.4962) (3725.1908 2916.0305) (3694.6565 2946.5649)
    ))
    ; P2575 -- see feature_dimensions_mm.csv
    ("06_ORNAMENT" 1 (
      (3689.313 5175.8321) (3691.0076 5172.687) (3694.6565 5170.6718) (3694.6565 5180.9924) (3691.0076 5178.9771)
    ))
    ; P2576 -- see feature_dimensions_mm.csv
    ("06_ORNAMENT" 1 (
      (3689.313 4864.3817) (3691.0076 4861.2366) (3694.6565 4859.2214) (3694.6565 4869.542) (3691.0076 4867.5267)
    ))
    ; P2577 -- see feature_dimensions_mm.csv
    ("06_ORNAMENT" 1 (
      (3689.313 4552.9313) (3691.0076 4549.7863) (3694.6565 4547.771) (3694.6565 4558.0916) (3691.0076 4556.0763)
    ))
    ; P2578 -- see feature_dimensions_mm.csv
    ("06_ORNAMENT" 1 (
      (3689.313 4241.4809) (3691.0076 4238.3359) (3694.6565 4236.3206) (3694.6565 4246.6412) (3691.0076 4244.626)
    ))
    ; P2579 -- see feature_dimensions_mm.csv
    ("06_ORNAMENT" 1 (
      (3689.313 3930.0305) (3691.0076 3926.8855) (3694.6565 3924.8702) (3694.6565 3935.1908) (3691.0076 3933.1756)
    ))
    ; P2580 -- see feature_dimensions_mm.csv
    ("06_ORNAMENT" 1 (
      (3793.084 5604.0153) (3825.2977 5582.1221) (3828.3511 5579.8473) (3846.1527 5565.4656) (3842.1069 5572.1527)
      (3841.1603 5573.3893) (3844.626 5570.8092) (3863.8168 5559.4962) (3884.2137 5550.0153) (3905.4809 5542.3359)
      (3927.2977 5536.4122) (3949.313 5532.2137) (3971.2214 5529.6794) (3992.687 5528.7786) (4013.3588 5529.4656)
      (4032.9313 5531.6947) (4051.0687 5535.4351) (4067.4504 5540.6412) (4054.5802 5554.0305) (4039.771 5566.9924)
      (4023.2366 5579.3282) (4005.2214 5590.855) (3985.9847 5601.3435) (3965.771 5610.6107) (3944.7939 5618.4427)
      (3923.3282 5624.6412) (3901.6031 5628.9924) (3879.8626 5631.3282) (3858.3359 5631.4046) (3837.2824 5629.0534)
      (3816.9466 5624.0458) (3797.5573 5616.1985)
    ))
    ; P2581 -- see feature_dimensions_mm.csv
    ("06_ORNAMENT" 1 (
      (3801.5267 5923.6641) (3804.6412 5913.8626) (3813.4656 5905.1298) (3826.6412 5898.2901) (3842.1221 5893.6336)
      (3857.6031 5890.8702) (3870.9313 5889.1756) (3880.4885 5887.313) (3885.4504 5883.9695) (3885.8626 5878.0153)
      (3882.7023 5868.8092) (3877.5115 5856.4122) (3872.1527 5841.6183) (3868.4427 5825.8779) (3867.7863 5811.0534)
      (3870.9313 5799.0382) (3877.8626 5791.4504) (3887.9084 5789.2366) (3899.8779 5792.5344) (3912.3969 5800.5191)
      (3924.1679 5811.5878) (3934.2901 5823.6183) (3942.4427 5834.3206) (3948.8244 5841.6641) (3954.1985 5844.2748)
      (3959.5725 5841.6641) (3965.9542 5834.3206) (3974.1069 5823.6183) (3984.229 5811.5878) (3996.0 5800.5191)
      (4008.5191 5792.5344) (4020.4885 5789.2366) (4030.5344 5791.4504) (4037.4656 5799.0382) (4040.6107 5811.0534)
      (4039.9542 5825.8779) (4036.2443 5841.6183) (4030.8855 5856.4122) (4025.6947 5868.8092) (4022.5344 5878.0153)
      (4022.9466 5883.9695) (4027.9084 5887.313) (4037.4656 5889.1756) (4050.7939 5890.8702) (4066.2748 5893.6336)
      (4081.7557 5898.2901) (4094.9313 5905.1298) (4103.7557 5913.8626) (4106.8702 5923.6641) (4103.7557 5933.4656)
      (4094.9313 5942.1985) (4081.7557 5949.0382) (4066.2748 5953.6947) (4050.7939 5956.458) (4037.4656 5958.1527)
      (4027.9084 5960.0153) (4022.9466 5963.3588) (4022.5344 5969.313) (4025.6947 5978.5191) (4030.8855 5990.916)
      (4036.2443 6005.7099) (4039.9542 6021.4351) (4040.6107 6036.2748) (4037.4656 6048.2901) (4030.5344 6055.8779)
      (4020.4885 6058.0916) (4008.5191 6054.7939) (3996.0 6046.8092) (3984.229 6035.7405) (3974.1069 6023.7099)
      (3965.9542 6013.0076) (3959.5725 6005.6641) (3954.1985 6003.0534) (3948.8244 6005.6641) (3942.4427 6013.0076)
      (3934.2901 6023.7099) (3924.1679 6035.7405) (3912.3969 6046.8092) (3899.8779 6054.7939) (3887.9084 6058.0916)
      (3877.8626 6055.8779) (3870.9313 6048.2901) (3867.7863 6036.2748) (3868.4427 6021.4351) (3872.1527 6005.7099)
      (3877.5115 5990.916) (3882.7023 5978.5191) (3885.8626 5969.313) (3885.4504 5963.3588) (3880.4885 5960.0153)
      (3870.9313 5958.1527) (3857.6031 5956.458) (3842.1221 5953.6947) (3826.6412 5949.0382) (3813.4656 5942.1985)
      (3804.6412 5933.4656)
    ))
    ; P2582 -- see feature_dimensions_mm.csv
    ("06_ORNAMENT" 1 (
      (3908.3969 5923.6641) (3910.6412 5909.5115) (3917.145 5896.7481) (3927.2824 5886.6107) (3940.0458 5880.1069)
      (3954.1985 5877.8626) (3968.3511 5880.1069) (3981.1145 5886.6107) (3991.2519 5896.7481) (3997.7557 5909.5115)
      (4000.0 5923.6641) (3997.7557 5937.8168) (3991.2519 5950.5802) (3981.1145 5960.7176) (3968.3511 5967.2214)
      (3954.1985 5969.4656) (3940.0458 5967.2214) (3927.2824 5960.7176) (3917.145 5950.5802) (3910.6412 5937.8168)
    ))
    ; P2583 -- see feature_dimensions_mm.csv
    ("06_ORNAMENT" 1 (
      (3945.7557 5428.1069) (3948.4885 5419.7863) (3949.7557 5415.1603) (3950.5191 5410.4275) (3953.9237 5378.9924)
      (3954.1985 5374.0458) (3954.1985 5211.7099) (3959.9542 5200.1985) (3969.6794 5184.4427) (3980.1679 5170.8397)
      (3988.3359 5187.5115) (3995.4504 5205.8779) (4001.374 5225.6336) (4006.0305 5246.5038) (4009.2977 5268.1679)
      (4011.0687 5290.3359) (4011.2519 5312.7176) (4009.7099 5335.0076) (4006.3664 5356.916) (4001.0992 5378.1527)
      (3993.8168 5398.3969) (3993.1145 5399.7863) (3996.0153 5396.5802) (4012.626 5381.7405) (4030.7786 5368.458)
      (4050.1374 5356.7786) (4070.3817 5346.7176) (4091.1603 5338.3053) (4112.1527 5331.542) (4133.0229 5326.4733)
      (4153.4351 5323.1145) (4173.0687 5321.4809) (4191.5878 5321.6031) (4208.6718 5323.5115) (4198.6565 5339.1603)
      (4186.6565 5354.7634) (4172.855 5370.0916) (4157.4351 5384.9008) (4140.6107 5398.9466) (4122.5954 5411.9847)
      (4103.5573 5423.7557) (4083.7099 5434.0153) (4063.2519 5442.5344) (4042.3664 5449.0534) (4021.2824 5453.3435)
      (4000.1832 5455.1298) (3979.2519 5454.1985) (3958.7023 5450.2901) (3947.313 5431.6489)
    ))
    ; P2584 -- see feature_dimensions_mm.csv
    ("06_ORNAMENT" 1 (
      (3954.1985 3007.6336) (3984.7328 2977.0992) (4015.2672 3007.6336) (3984.7328 3038.1679)
    ))
    ; P2585 -- see feature_dimensions_mm.csv
    ("06_ORNAMENT" 1 (
      (3954.1985 2916.0305) (3984.7328 2885.4962) (4015.2672 2916.0305) (3984.7328 2946.5649)
    ))
    ; P2586 -- see feature_dimensions_mm.csv
    ("06_ORNAMENT" 1 (
      (3986.9924 4005.2061) (4000.0305 3989.6947) (4015.2214 3973.6336) (4032.3206 3957.2977) (4051.0687 3940.9466)
      (4071.2366 3924.8092) (4092.5496 3909.1756) (4114.7786 3894.2595) (4137.6489 3880.3511) (4160.9466 3867.6947)
      (4184.3969 3856.5344) (4207.7557 3847.1298) (4230.7786 3839.7557) (4233.771 3839.0687) (4231.084 3832.5954)
      (4229.0076 3816.7939) (4231.084 3800.9924) (4237.1908 3786.2595) (4246.9008 3773.6183) (4259.542 3763.9084)
      (4274.2748 3757.8015) (4290.0763 3755.7252) (4305.8779 3757.8015) (4320.6107 3763.9084) (4333.2519 3773.6183)
      (4342.9618 3786.2595) (4349.0687 3800.9924) (4351.145 3816.7939) (4349.0687 3832.5954) (4342.9618 3847.3282)
      (4333.2519 3859.9695) (4320.6107 3869.6794) (4310.2137 3873.9847) (4318.3206 3886.0458) (4325.4809 3878.1069)
      (4345.8779 3858.7176) (4367.2061 3841.771) (4389.3588 3827.6641) (4412.2137 3816.7939) (4408.9313 3843.2519)
      (4402.4733 3870.0305) (4395.374 3890.458) (4395.5573 3890.5649) (4409.0076 3899.6183) (4421.6183 3910.1832)
      (4433.3282 3921.9847) (4444.0916 3934.8244) (4453.8473 3948.4427) (4462.5191 3962.5954) (4470.0458 3977.0687)
      (4476.3817 3991.6183) (4481.4656 4006.0) (4485.2214 4019.9847) (4487.6031 4033.3282) (4488.5496 4045.8015)
      (4476.2595 4040.0763) (4463.7252 4032.916) (4451.145 4024.4427) (4438.7176 4014.7481) (4426.6412 4003.9695)
      (4415.1145 3992.229) (4404.3206 3979.6336) (4394.4885 3966.3206) (4385.7863 3952.3969) (4378.4427 3937.9847)
      (4376.3817 3932.7481) (4367.2672 3949.7557) (4357.8779 3964.855) (4365.6183 3985.0534) (4374.0916 4010.4885)
      (4381.2977 4035.6794) (4387.1756 4060.2748) (4391.6947 4083.8931) (4394.7786 4106.1527) (4396.4122 4126.687)
      (4396.5191 4145.1145) (4383.4504 4129.6336) (4370.2137 4111.9237) (4357.0229 4092.3053) (4344.0763 4071.0382)
      (4331.6183 4048.4427) (4319.8168 4024.7786) (4317.771 4020.1832) (4315.4809 4023.0687) (4306.916 4032.6718)
      (4306.8855 4033.7099) (4305.0229 4059.8473) (4302.1069 4084.9771) (4300.7939 4093.0076) (4305.8779 4093.6794)
      (4320.6107 4099.7863) (4333.2519 4109.4962) (4342.9618 4122.1374) (4349.0687 4136.8702) (4351.145 4152.6718)
      (4349.0687 4168.4733) (4342.9618 4183.2061) (4333.2519 4195.8473) (4320.6107 4205.5573) (4305.8779 4211.6641)
      (4290.0763 4213.7405) (4274.2748 4211.6641) (4259.542 4205.5573) (4246.9008 4195.8473) (4237.1908 4183.2061)
      (4231.084 4168.4733) (4229.0076 4152.6718) (4231.084 4136.8702) (4237.1908 4122.1374) (4246.9008 4109.4962)
      (4259.542 4099.7863) (4261.6336 4098.916) (4258.1069 4081.145) (4256.1679 4082.8702) (4236.3206 4098.5954)
      (4216.9618 4111.771) (4198.4733 4122.1374) (4203.1298 4099.4351) (4203.9847 4096.3664) (4201.9695 4099.9695)
      (4189.9847 4118.9924) (4178.0153 4135.7405) (4166.229 4149.9084) (4166.1985 4129.6336) (4167.4809 4107.5725)
      (4170.0305 4084.0611) (4173.8321 4059.4809) (4178.855 4034.1527) (4185.084 4008.458) (4192.4733 3982.7328)
      (4193.7099 3979.0687) (4187.2824 3986.9466) (4169.4351 4006.9618) (4151.1603 4025.7405) (4132.7634 4043.084)
      (4114.5191 4058.7481) (4096.7481 4072.5038) (4079.7405 4084.1374) (4063.8168 4093.4046) (4070.7481 4074.3511)
      (4079.5115 4054.0611) (4089.9695 4032.855) (4101.9695 4011.0687) (4115.3893 3988.9924) (4130.0458 3966.9924)
      (4145.8015 3945.374) (4148.229 3942.3511) (4139.4809 3947.542) (4115.8626 3960.229) (4092.2443 3971.6031)
      (4069.0076 3981.5878) (4046.5038 3990.0458) (4025.0992 3996.8702) (4005.145 4001.9695)
    ))
    ; P2587 -- see feature_dimensions_mm.csv
    ("06_ORNAMENT" 1 (
      (4015.2672 5709.9237) (4091.6031 5633.5878) (4167.9389 5709.9237) (4091.6031 5786.2595)
    ))
    ; P2588 -- see feature_dimensions_mm.csv
    ("06_ORNAMENT" 1 (
      (4022.3053 5095.1603) (4023.145 5073.1298) (4025.5267 5051.7863) (4029.3588 5031.4504) (4034.5649 5012.4427)
      (4041.0229 4995.084) (4048.6718 4979.7099) (4059.9389 4994.458) (4070.4885 5011.084) (4080.1527 5029.313)
      (4088.7939 5048.8702) (4096.229 5069.4809) (4102.2901 5090.8702) (4106.8244 5112.7939) (4109.6641 5134.9618)
      (4110.6718 5157.0992) (4109.6336 5178.9466) (4106.4427 5200.229) (4106.0305 5201.7252) (4108.2443 5198.0153)
      (4121.6489 5180.2137) (4136.855 5163.6489) (4153.5725 5148.4275) (4171.4504 5134.6107) (4190.1985 5122.2901)
      (4201.2672 5116.1221) (4203.1298 5107.0687) (4209.8931 5082.9466) (4218.626 5057.8168) (4229.2214 5032.0458)
      (4237.145 5015.3588) (4222.0763 5025.5115) (4203.2672 5035.2519) (4183.5725 5042.3969) (4163.084 5046.6412)
      (4145.4351 5033.7863) (4129.6489 5018.6412) (4115.7099 5001.5725) (4103.5725 4982.8855) (4093.2366 4962.916)
      (4084.6565 4942.0) (4077.8015 4920.458) (4072.6412 4898.6412) (4069.1756 4876.855) (4067.3435 4855.4656)
      (4067.145 4834.7634) (4068.5344 4815.1145) (4071.4962 4796.8397) (4075.9847 4780.2595) (4089.9084 4792.5344)
      (4103.4962 4806.7786) (4116.5496 4822.7634) (4128.8244 4840.2595) (4140.1374 4859.0229) (4150.2595 4878.8244)
      (4158.9924 4899.4351) (4166.1069 4920.626) (4171.3893 4942.1374) (4174.6565 4963.771) (4175.6641 4985.2672)
      (4175.5573 4986.8244) (4177.0076 4982.7481) (4186.6718 4962.6718) (4198.3664 4943.4656) (4211.7863 4925.2672)
      (4226.626 4908.229) (4242.6107 4892.4885) (4259.4198 4878.2137) (4260.2443 4877.6031) (4259.542 4877.313)
      (4246.9008 4867.6031) (4237.1908 4854.9618) (4231.084 4840.229) (4229.0076 4824.4275) (4231.084 4808.626)
      (4231.3282 4808.0305) (4217.7252 4816.2595) (4198.4733 4824.4275) (4178.6565 4815.2672) (4160.2137 4803.4962)
      (4143.2061 4789.4656) (4127.6641 4773.5115) (4113.6336 4755.9389) (4101.1298 4737.0992) (4090.1985 4717.313)
      (4080.9008 4696.916) (4073.2366 4676.229) (4067.2672 4655.6031) (4063.0382 4635.3435) (4060.5649 4615.8015)
      (4059.8931 4597.2977) (4061.0687 4580.1527) (4077.1298 4589.4809) (4093.2366 4600.7939) (4109.145 4613.9389)
      (4124.6107 4628.687) (4139.3588 4644.9008) (4153.1603 4662.3511) (4165.7252 4680.855) (4176.8397 4700.2443)
      (4186.229 4720.3206) (4193.6489 4740.8855) (4198.8397 4761.771) (4199.0382 4763.3282) (4199.6489 4759.0382)
      (4205.2214 4737.4656) (4212.9466 4716.3511) (4222.5496 4695.8779) (4233.7863 4676.2748) (4246.3969 4657.7252)
      (4252.3511 4650.1985) (4255.5573 4644.2748) (4271.0534 4618.9313) (4287.9542 4594.4733) (4306.1374 4571.3282)
      (4325.4809 4549.8626) (4345.8779 4530.4733) (4367.2061 4513.5267) (4389.3588 4499.4198) (4412.2137 4488.5496)
      (4408.9313 4515.0076) (4402.4733 4541.7863) (4395.374 4562.2137) (4395.5573 4562.3206) (4409.0076 4571.374)
      (4421.6183 4581.9389) (4433.3282 4593.7405) (4444.0916 4606.5802) (4453.8473 4620.1985) (4462.5191 4634.3511)
      (4470.0458 4648.8244) (4476.3817 4663.374) (4481.4656 4677.7557) (4485.2214 4691.7405) (4487.6031 4705.084)
      (4488.5496 4717.5573) (4476.2595 4711.8321) (4463.7252 4704.6718) (4451.145 4696.1985) (4438.7176 4686.5038)
      (4426.6412 4675.7252) (4415.1145 4663.9847) (4404.3206 4651.3893) (4394.4885 4638.0763) (4385.7863 4624.1527)
      (4378.4427 4609.7405) (4376.3817 4604.5038) (4367.2672 4621.5115) (4351.4046 4647.0076) (4334.0153 4671.5267)
      (4316.3664 4693.6947) (4313.4504 4701.5267) (4304.1679 4721.8931) (4293.374 4741.4504) (4281.084 4759.9084)
      (4276.9008 4765.0992) (4290.0763 4763.3588) (4305.8779 4765.4351) (4320.6107 4771.542) (4333.2519 4781.2519)
      (4342.9618 4793.8931) (4349.0687 4808.626) (4351.145 4824.4275) (4349.0687 4840.229) (4342.9618 4854.9618)
      (4340.7023 4857.9084) (4337.1298 4871.1603) (4335.2672 4876.4427) (4345.8779 4866.3511) (4367.2061 4849.4046)
      (4389.3588 4835.2977) (4412.2137 4824.4275) (4408.9313 4850.8855) (4402.4733 4877.6641) (4395.374 4898.0916)
      (4395.5573 4898.1985) (4409.0076 4907.2519) (4421.6183 4917.8168) (4433.3282 4929.6183) (4444.0916 4942.458)
      (4453.8473 4956.0763) (4462.5191 4970.229) (4470.0458 4984.7023) (4476.3817 4999.2519) (4481.4656 5013.6336)
      (4485.2214 5027.6183) (4487.6031 5040.9618) (4488.5496 5053.4351) (4476.2595 5047.7099) (4463.7252 5040.5496)
      (4451.145 5032.0763) (4438.7176 5022.3817) (4426.6412 5011.6031) (4415.1145 4999.8626) (4404.3206 4987.2672)
      (4394.4885 4973.9542) (4385.7863 4960.0305) (4378.4427 4945.6183) (4376.3817 4940.3817) (4367.2672 4957.3893)
      (4351.4046 4982.8855) (4334.0153 5007.4046) (4315.4809 5030.7023) (4296.0916 5052.4733) (4276.2137 5072.5038)
      (4256.1679 5090.5038) (4251.2519 5094.3969) (4267.2519 5089.8168) (4285.4351 5086.3206) (4302.5496 5084.8702)
      (4296.6107 5100.0916) (4305.8779 5101.313) (4320.6107 5107.4198) (4333.2519 5117.1298) (4342.9618 5129.771)
      (4349.0687 5144.5038) (4351.145 5160.3053) (4349.0687 5176.1069) (4342.9618 5190.8397) (4333.2519 5203.4809)
      (4320.6107 5213.1908) (4305.8779 5219.2977) (4290.0763 5221.374) (4274.2748 5219.2977) (4259.542 5213.1908)
      (4246.9008 5203.4809) (4237.1908 5190.8397) (4235.9389 5187.8321) (4235.3893 5188.4275) (4219.0229 5203.6794)
      (4201.5573 5217.6183) (4183.145 5229.9695) (4163.9542 5240.4427) (4144.1069 5248.7481) (4123.7557 5254.626)
      (4103.0382 5257.8015) (4082.1374 5257.9695) (4067.3282 5241.9084) (4054.7939 5223.9847) (4044.458 5204.5191)
      (4036.1985 5183.8168) (4029.9542 5162.2137) (4025.6183 5140.0305) (4023.0992 5117.5725)
    ))
    ; P2589 -- see feature_dimensions_mm.csv
    ("06_ORNAMENT" 1 (
      (4122.1374 7374.0458) (4183.2061 7343.5115) (4244.2748 7374.0458) (4183.2061 7404.5802)
    ))
    ; P2590 -- see feature_dimensions_mm.csv
    ("06_ORNAMENT" 1 (
      (4122.1374 7282.4427) (4183.2061 7251.9084) (4244.2748 7282.4427) (4183.2061 7312.9771)
    ))
    ; P2591 -- see feature_dimensions_mm.csv
    ("06_ORNAMENT" 1 (
      (4122.1374 7190.8397) (4183.2061 7160.3053) (4244.2748 7190.8397) (4183.2061 7221.374)
    ))
    ; P2592 -- see feature_dimensions_mm.csv
    ("06_ORNAMENT" 1 (
      (4122.1374 6122.1374) (4198.4733 6045.8015) (4274.8092 6122.1374) (4198.4733 6198.4733)
    ))
    ; P2593 -- see feature_dimensions_mm.csv
    ("06_ORNAMENT" 1 (
      (4198.4733 5801.5267) (4203.1298 5778.8244) (4209.8931 5754.7023) (4218.626 5729.5725) (4229.2214 5703.8015)
      (4241.5725 5677.7863) (4255.5573 5651.9084) (4271.0534 5626.5649) (4287.9542 5602.1069) (4306.1374 5578.9618)
      (4325.4809 5557.4962) (4345.8779 5538.1069) (4367.2061 5521.1603) (4389.3588 5507.0534) (4412.2137 5496.1832)
      (4408.9313 5522.6412) (4402.4733 5549.4198) (4395.374 5569.8473) (4395.5573 5569.9542) (4409.0076 5579.0076)
      (4421.6183 5589.5725) (4433.3282 5601.374) (4444.0916 5614.2137) (4453.8473 5627.8321) (4462.5191 5641.9847)
      (4470.0458 5656.458) (4476.3817 5671.0076) (4481.4656 5685.3893) (4485.2214 5699.374) (4487.6031 5712.7176)
      (4488.5496 5725.1908) (4476.2595 5719.4656) (4463.7252 5712.3053) (4451.145 5703.8321) (4438.7176 5694.1374)
      (4426.6412 5683.3588) (4415.1145 5671.6183) (4404.3206 5659.0229) (4394.4885 5645.7099) (4385.7863 5631.7863)
      (4378.4427 5617.374) (4376.3817 5612.1374) (4367.2672 5629.145) (4351.4046 5654.6412) (4334.0153 5679.1603)
      (4315.4809 5702.458) (4296.0916 5724.229) (4276.2137 5744.2595) (4256.1679 5762.2595) (4236.3206 5777.9847)
      (4216.9618 5791.1603)
    ))
    ; P2594 -- see feature_dimensions_mm.csv
    ("06_ORNAMENT" 1 (
      (4198.4733 5465.6489) (4203.1298 5442.9466) (4209.8931 5418.8244) (4218.626 5393.6947) (4229.2214 5367.9237)
      (4241.5725 5341.9084) (4255.5573 5316.0305) (4271.0534 5290.687) (4287.9542 5266.229) (4306.1374 5243.084)
      (4325.4809 5221.6183) (4345.8779 5202.229) (4367.2061 5185.2824) (4389.3588 5171.1756) (4412.2137 5160.3053)
      (4408.9313 5186.7634) (4402.4733 5213.542) (4395.374 5233.9695) (4395.5573 5234.0763) (4409.0076 5243.1298)
      (4421.6183 5253.6947) (4433.3282 5265.4962) (4444.0916 5278.3359) (4453.8473 5291.9542) (4462.5191 5306.1069)
      (4470.0458 5320.5802) (4476.3817 5335.1298) (4481.4656 5349.5115) (4485.2214 5363.4962) (4487.6031 5376.8397)
      (4488.5496 5389.313) (4476.2595 5383.5878) (4463.7252 5376.4275) (4451.145 5367.9542) (4438.7176 5358.2595)
      (4426.6412 5347.4809) (4415.1145 5335.7405) (4404.3206 5323.145) (4394.4885 5309.8321) (4385.7863 5295.9084)
      (4378.4427 5281.4962) (4376.3817 5276.2595) (4367.2672 5293.2672) (4359.3893 5305.9542) (4396.9466 5343.5115)
      (4320.6107 5419.8473) (4292.626 5391.8626) (4276.2137 5408.3817) (4256.1679 5426.3817) (4236.3206 5442.1069)
      (4216.9618 5455.2824)
    ))
    ; P2595 -- see feature_dimensions_mm.csv
    ("06_ORNAMENT" 1 (
      (4198.4733 4458.0153) (4203.1298 4435.313) (4209.8931 4411.1908) (4218.626 4386.0611) (4229.2214 4360.2901)
      (4241.5725 4334.2748) (4255.5573 4308.3969) (4271.0534 4283.0534) (4287.9542 4258.5954) (4306.1374 4235.4504)
      (4325.4809 4213.9847) (4345.8779 4194.5954) (4367.2061 4177.6489) (4389.3588 4163.542) (4412.2137 4152.6718)
      (4408.9313 4179.1298) (4402.4733 4205.9084) (4395.374 4226.3359) (4395.5573 4226.4427) (4409.0076 4235.4962)
      (4421.6183 4246.0611) (4433.3282 4257.8626) (4444.0916 4270.7023) (4453.8473 4284.3206) (4462.5191 4298.4733)
      (4470.0458 4312.9466) (4476.3817 4327.4962) (4481.4656 4341.8779) (4485.2214 4355.8626) (4487.6031 4369.2061)
      (4488.5496 4381.6794) (4476.2595 4375.9542) (4463.7252 4368.7939) (4451.145 4360.3206) (4438.7176 4350.626)
      (4426.6412 4339.8473) (4415.1145 4328.1069) (4404.3206 4315.5115) (4394.4885 4302.1985) (4385.7863 4288.2748)
      (4378.4427 4273.8626) (4376.3817 4268.626) (4367.2672 4285.6336) (4359.3893 4298.3206) (4427.4809 4366.4122)
      (4351.145 4442.7481) (4292.626 4384.229) (4276.2137 4400.7481) (4256.1679 4418.7481) (4236.3206 4434.4733)
      (4216.9618 4447.6489)
    ))
    ; P2596 -- see feature_dimensions_mm.csv
    ("06_ORNAMENT" 1 (
      (4229.0076 5496.1832) (4231.084 5480.3817) (4237.1908 5465.6489) (4246.9008 5453.0076) (4259.542 5443.2977)
      (4274.2748 5437.1908) (4290.0763 5435.1145) (4305.8779 5437.1908) (4320.6107 5443.2977) (4333.2519 5453.0076)
      (4342.9618 5465.6489) (4349.0687 5480.3817) (4351.145 5496.1832) (4349.0687 5511.9847) (4342.9618 5526.7176)
      (4333.2519 5539.3588) (4320.6107 5549.0687) (4305.8779 5555.1756) (4290.0763 5557.2519) (4274.2748 5555.1756)
      (4259.542 5549.0687) (4246.9008 5539.3588) (4237.1908 5526.7176) (4231.084 5511.9847)
    ))
    ; P2597 -- see feature_dimensions_mm.csv
    ("06_ORNAMENT" 1 (
      (4229.0076 4488.5496) (4231.084 4472.7481) (4237.1908 4458.0153) (4246.9008 4445.374) (4259.542 4435.6641)
      (4274.2748 4429.5573) (4290.0763 4427.4809) (4305.8779 4429.5573) (4320.6107 4435.6641) (4333.2519 4445.374)
      (4342.9618 4458.0153) (4349.0687 4472.7481) (4351.145 4488.5496) (4349.0687 4504.3511) (4342.9618 4519.084)
      (4333.2519 4531.7252) (4320.6107 4541.4351) (4305.8779 4547.542) (4290.0763 4549.6183) (4274.2748 4547.542)
      (4259.542 4541.4351) (4246.9008 4531.7252) (4237.1908 4519.084) (4231.084 4504.3511)
    ))
    ; P2598 -- see feature_dimensions_mm.csv
    ("06_ORNAMENT" 1 (
      (4610.687 7374.0458) (4671.7557 7343.5115) (4732.8244 7374.0458) (4671.7557 7404.5802)
    ))
    ; P2599 -- see feature_dimensions_mm.csv
    ("06_ORNAMENT" 1 (
      (4610.687 7282.4427) (4671.7557 7251.9084) (4732.8244 7282.4427) (4671.7557 7312.9771)
    ))
    ; P2600 -- see feature_dimensions_mm.csv
    ("06_ORNAMENT" 1 (
      (4610.687 7190.8397) (4671.7557 7160.3053) (4732.8244 7190.8397) (4671.7557 7221.374)
    ))
    ; P2601 -- see feature_dimensions_mm.csv
    ("06_ORNAMENT" 1 (
      (8854.9618 2717.5573) (8856.8244 2711.6794) (8862.1221 2706.4427) (8870.0305 2702.3359) (8879.313 2699.542)
      (8888.6107 2697.8779) (8896.6107 2696.8702) (8902.3359 2695.7557) (8905.313 2693.7405) (8905.5725 2690.1679)
      (8903.6641 2684.6412) (8900.5496 2677.2061) (8897.3435 2668.3359) (8895.1145 2658.8855) (8894.7176 2649.9847)
      (8896.5954 2642.7786) (8900.7634 2638.229) (8906.7939 2636.9008) (8913.9695 2638.8702) (8921.4809 2643.6641)
      (8928.5496 2650.3053) (8934.626 2657.5267) (8939.5115 2663.9542) (8943.3435 2668.3511) (8946.5649 2669.9237)
      (8949.7863 2668.3511) (8953.6183 2663.9542) (8958.5038 2657.5267) (8964.5802 2650.3053) (8971.6489 2643.6641)
      (8979.1603 2638.8702) (8986.3359 2636.9008) (8992.3664 2638.229) (8996.5344 2642.7786) (8998.4122 2649.9847)
      (8998.0153 2658.8855) (8995.7863 2668.3359) (8992.5802 2677.2061) (8989.4656 2684.6412) (8987.5573 2690.1679)
      (8987.8168 2693.7405) (8990.7939 2695.7557) (8996.5191 2696.8702) (9004.5191 2697.8779) (9013.8168 2699.542)
      (9023.0992 2702.3359) (9031.0076 2706.4427) (9036.3053 2711.6794) (9038.1679 2717.5573) (9036.3053 2723.4351)
      (9031.0076 2728.6718) (9023.0992 2732.7786) (9013.8168 2735.5725) (9004.5191 2737.2366) (8996.5191 2738.2443)
      (8990.7939 2739.3588) (8987.8168 2741.374) (8987.5573 2744.9466) (8989.4656 2750.4733) (8992.5802 2757.9084)
      (8995.7863 2766.7786) (8998.0153 2776.229) (8998.4122 2785.1298) (8996.5344 2792.3359) (8992.3664 2796.8855)
      (8986.3359 2798.2137) (8979.1603 2796.2443) (8971.6489 2791.4504) (8964.5802 2784.8092) (8958.5038 2777.5878)
      (8953.6183 2771.1603) (8949.7863 2766.7634) (8946.5649 2765.1908) (8943.3435 2766.7634) (8939.5115 2771.1603)
      (8934.626 2777.5878) (8928.5496 2784.8092) (8921.4809 2791.4504) (8913.9695 2796.2443) (8906.7939 2798.2137)
      (8900.7634 2796.8855) (8896.5954 2792.3359) (8894.7176 2785.1298) (8895.1145 2776.229) (8897.3435 2766.7786)
      (8900.5496 2757.9084) (8903.6641 2750.4733) (8905.5725 2744.9466) (8905.313 2741.374) (8902.3359 2739.3588)
      (8896.6107 2738.2443) (8888.6107 2737.2366) (8879.313 2735.5725) (8870.0305 2732.7786) (8862.1221 2728.6718)
      (8856.8244 2723.4351)
    ))
    ; P2602 -- see feature_dimensions_mm.csv
    ("06_ORNAMENT" 1 (
      (8885.8931 2915.6641) (8886.5954 2907.0382) (8888.6718 2898.9618) (8892.1679 2891.5878) (8897.1603 2885.0534)
      (8903.7099 2879.5115) (8911.8473 2875.1145) (8921.6794 2872.0) (8933.2214 2870.3206) (8946.5649 2870.229)
      (8954.3053 2881.3282) (8959.7252 2891.9237) (8962.9771 2901.9542) (8964.2137 2911.374) (8963.6031 2920.1374)
      (8961.2977 2928.1832) (8957.4504 2935.4962) (8952.229 2942.0153) (8945.7863 2947.6947) (8938.2901 2952.4885)
      (8929.8626 2956.3359) (8920.7023 2959.2061) (8910.9466 2961.0534) (8900.7634 2961.8321) (8895.542 2952.687)
      (8891.374 2943.3435) (8888.3359 2933.9695) (8886.4885 2924.687)
    ))
    ; P2603 -- see feature_dimensions_mm.csv
    ("06_ORNAMENT" 1 (
      (8920.6107 2717.5573) (8921.8779 2709.542) (8925.5725 2702.3053) (8931.313 2696.5649) (8938.5496 2692.8702)
      (8946.5649 2691.6031) (8954.5802 2692.8702) (8961.8168 2696.5649) (8967.5573 2702.3053) (8971.2519 2709.542)
      (8972.5191 2717.5573) (8971.2519 2725.5725) (8967.5573 2732.8092) (8961.8168 2738.5496) (8954.5802 2742.2443)
      (8946.5649 2743.5115) (8938.5496 2742.2443) (8931.313 2738.5496) (8925.5725 2732.8092) (8921.8779 2725.5725)
    ))
    ; P2604 -- see feature_dimensions_mm.csv
    ("06_ORNAMENT" 1 (
      (8971.7557 5142.0305) (8973.374 5139.0382) (8977.7863 5136.5954) (8983.8015 5135.0229) (8989.8321 5134.1985)
      (8994.3359 5133.6336) (8996.3511 5132.6107) (8995.6489 5130.4733) (8992.855 5126.8855) (8989.1756 5122.0458)
      (8986.0458 5116.687) (8984.6412 5111.8321) (8985.6183 5108.5649) (8988.8855 5107.6031) (8993.7252 5108.9924)
      (8999.0992 5112.1221) (9003.9389 5115.8015) (9007.5267 5118.5954) (9009.6641 5119.2977) (9010.687 5117.2977)
      (9011.2519 5112.7786) (9012.0611 5106.7634) (9013.6489 5100.7481) (9016.0916 5096.3206) (9019.084 5094.7023)
      (9022.0763 5096.3206) (9024.5191 5100.7481) (9026.1069 5106.7634) (9026.9313 5112.7786) (9027.4809 5117.2977)
      (9028.5038 5119.2977) (9030.6412 5118.5954) (9034.229 5115.8015) (9039.0687 5112.1221) (9044.4427 5108.9924)
      (9049.2824 5107.6031) (9052.5496 5108.5649) (9053.5267 5111.8321) (9052.1221 5116.687) (9048.9924 5122.0458)
      (9045.313 5126.8855) (9042.5191 5130.4733) (9041.8168 5132.6107) (9043.8321 5133.6336) (9048.3359 5134.1985)
      (9054.3664 5135.0229) (9060.3817 5136.5954) (9064.7939 5139.0382) (9066.4122 5142.0305) (9064.7939 5145.0382)
      (9060.3817 5147.4656) (9054.3664 5149.0534) (9048.3359 5149.8779) (9043.8321 5150.4427) (9041.8168 5151.4504)
      (9042.5191 5153.5878) (9045.313 5157.1756) (9048.9924 5162.0153) (9052.1221 5167.3893) (9053.5267 5172.2443)
      (9052.5496 5175.4962) (9049.2824 5176.4733) (9044.4427 5175.084) (9039.0687 5171.9389) (9034.229 5168.2748)
      (9030.6412 5165.4809) (9028.5038 5164.7786) (9027.4809 5166.7786) (9026.9313 5171.2977) (9026.1069 5177.313)
      (9024.5191 5183.3282) (9022.0763 5187.7405) (9019.084 5189.3588) (9016.0916 5187.7405) (9013.6489 5183.3282)
      (9012.0611 5177.313) (9011.2519 5171.2977) (9010.687 5166.7786) (9009.6641 5164.7786) (9007.5267 5165.4809)
      (9003.9389 5168.2748) (8999.0992 5171.9389) (8993.7252 5175.084) (8988.8855 5176.4733) (8985.6183 5175.4962)
      (8984.6412 5172.2443) (8986.0458 5167.3893) (8989.1756 5162.0153) (8992.855 5157.1756) (8995.6489 5153.5878)
      (8996.3511 5151.4504) (8994.3359 5150.4427) (8989.8321 5149.8779) (8983.8015 5149.0534) (8977.7863 5147.4656)
      (8973.374 5145.0382)
    ))
    ; P2605 -- see feature_dimensions_mm.csv
    ("06_ORNAMENT" 1 (
      (8971.7557 4851.9542) (8973.374 4848.9618) (8977.7863 4846.5191) (8983.8015 4844.9466) (8989.8321 4844.1221)
      (8994.3359 4843.5573) (8996.3511 4842.5344) (8995.6489 4840.3969) (8992.855 4836.8092) (8989.1756 4831.9695)
      (8986.0458 4826.6107) (8984.6412 4821.7557) (8985.6183 4818.4885) (8988.8855 4817.5267) (8993.7252 4818.916)
      (8999.0992 4822.0458) (9003.9389 4825.7252) (9007.5267 4828.5191) (9009.6641 4829.2214) (9010.687 4827.2214)
      (9011.2519 4822.7023) (9012.0611 4816.687) (9013.6489 4810.6718) (9016.0916 4806.2443) (9019.084 4804.626)
      (9022.0763 4806.2443) (9024.5191 4810.6718) (9026.1069 4816.687) (9026.9313 4822.7023) (9027.4809 4827.2214)
      (9028.5038 4829.2214) (9030.6412 4828.5191) (9034.229 4825.7252) (9039.0687 4822.0458) (9044.4427 4818.916)
      (9049.2824 4817.5267) (9052.5496 4818.4885) (9053.5267 4821.7557) (9052.1221 4826.6107) (9048.9924 4831.9695)
      (9045.313 4836.8092) (9042.5191 4840.3969) (9041.8168 4842.5344) (9043.8321 4843.5573) (9048.3359 4844.1221)
      (9054.3664 4844.9466) (9060.3817 4846.5191) (9064.7939 4848.9618) (9066.4122 4851.9542) (9064.7939 4854.9618)
      (9060.3817 4857.3893) (9054.3664 4858.9771) (9048.3359 4859.8015) (9043.8321 4860.3664) (9041.8168 4861.374)
      (9042.5191 4863.5115) (9045.313 4867.0992) (9048.9924 4871.9389) (9052.1221 4877.313) (9053.5267 4882.1679)
      (9052.5496 4885.4198) (9049.2824 4886.3969) (9044.4427 4885.0076) (9039.0687 4881.8626) (9034.229 4878.1985)
      (9030.6412 4875.4046) (9028.5038 4874.7023) (9027.4809 4876.7023) (9026.9313 4881.2214) (9026.1069 4887.2366)
      (9024.5191 4893.2519) (9022.0763 4897.6641) (9019.084 4899.2824) (9016.0916 4897.6641) (9013.6489 4893.2519)
      (9012.0611 4887.2366) (9011.2519 4881.2214) (9010.687 4876.7023) (9009.6641 4874.7023) (9007.5267 4875.4046)
      (9003.9389 4878.1985) (8999.0992 4881.8626) (8993.7252 4885.0076) (8988.8855 4886.3969) (8985.6183 4885.4198)
      (8984.6412 4882.1679) (8986.0458 4877.313) (8989.1756 4871.9389) (8992.855 4867.0992) (8995.6489 4863.5115)
      (8996.3511 4861.374) (8994.3359 4860.3664) (8989.8321 4859.8015) (8983.8015 4858.9771) (8977.7863 4857.3893)
      (8973.374 4854.9618)
    ))
    ; P2606 -- see feature_dimensions_mm.csv
    ("06_ORNAMENT" 1 (
      (8971.7557 4561.8779) (8973.374 4558.8855) (8977.7863 4556.4427) (8983.8015 4554.8702) (8989.8321 4554.0458)
      (8994.3359 4553.4809) (8996.3511 4552.458) (8995.6489 4550.3206) (8992.855 4546.7328) (8989.1756 4541.8931)
      (8986.0458 4536.5344) (8984.6412 4531.6794) (8985.6183 4528.4122) (8988.8855 4527.4504) (8993.7252 4528.8397)
      (8999.0992 4531.9695) (9003.9389 4535.6489) (9007.5267 4538.4427) (9009.6641 4539.145) (9010.687 4537.145)
      (9011.2519 4532.626) (9012.0611 4526.6107) (9013.6489 4520.5954) (9016.0916 4516.1679) (9019.084 4514.5496)
      (9022.0763 4516.1679) (9024.5191 4520.5954) (9026.1069 4526.6107) (9026.9313 4532.626) (9027.4809 4537.145)
      (9028.5038 4539.145) (9030.6412 4538.4427) (9034.229 4535.6489) (9039.0687 4531.9695) (9044.4427 4528.8397)
      (9049.2824 4527.4504) (9052.5496 4528.4122) (9053.5267 4531.6794) (9052.1221 4536.5344) (9048.9924 4541.8931)
      (9045.313 4546.7328) (9042.5191 4550.3206) (9041.8168 4552.458) (9043.8321 4553.4809) (9048.3359 4554.0458)
      (9054.3664 4554.8702) (9060.3817 4556.4427) (9064.7939 4558.8855) (9066.4122 4561.8779) (9064.7939 4564.8855)
      (9060.3817 4567.313) (9054.3664 4568.9008) (9048.3359 4569.7252) (9043.8321 4570.2901) (9041.8168 4571.2977)
      (9042.5191 4573.4351) (9045.313 4577.0229) (9048.9924 4581.8626) (9052.1221 4587.2366) (9053.5267 4592.0916)
      (9052.5496 4595.3435) (9049.2824 4596.3206) (9044.4427 4594.9313) (9039.0687 4591.7863) (9034.229 4588.1221)
      (9030.6412 4585.3282) (9028.5038 4584.626) (9027.4809 4586.626) (9026.9313 4591.145) (9026.1069 4597.1603)
      (9024.5191 4603.1756) (9022.0763 4607.5878) (9019.084 4609.2061) (9016.0916 4607.5878) (9013.6489 4603.1756)
      (9012.0611 4597.1603) (9011.2519 4591.145) (9010.687 4586.626) (9009.6641 4584.626) (9007.5267 4585.3282)
      (9003.9389 4588.1221) (8999.0992 4591.7863) (8993.7252 4594.9313) (8988.8855 4596.3206) (8985.6183 4595.3435)
      (8984.6412 4592.0916) (8986.0458 4587.2366) (8989.1756 4581.8626) (8992.855 4577.0229) (8995.6489 4573.4351)
      (8996.3511 4571.2977) (8994.3359 4570.2901) (8989.8321 4569.7252) (8983.8015 4568.9008) (8977.7863 4567.313)
      (8973.374 4564.8855)
    ))
    ; P2607 -- see feature_dimensions_mm.csv
    ("06_ORNAMENT" 1 (
      (8971.7557 4271.8015) (8973.374 4268.8092) (8977.7863 4266.3664) (8983.8015 4264.7939) (8989.8321 4263.9695)
      (8994.3359 4263.4046) (8996.3511 4262.3817) (8995.6489 4260.2443) (8992.855 4256.6565) (8989.1756 4251.8168)
      (8986.0458 4246.458) (8984.6412 4241.6031) (8985.6183 4238.3359) (8988.8855 4237.374) (8993.7252 4238.7634)
      (8999.0992 4241.8931) (9003.9389 4245.5725) (9007.5267 4248.3664) (9009.6641 4249.0687) (9010.687 4247.0687)
      (9011.2519 4242.5496) (9012.0611 4236.5344) (9013.6489 4230.5191) (9016.0916 4226.0916) (9019.084 4224.4733)
      (9022.0763 4226.0916) (9024.5191 4230.5191) (9026.1069 4236.5344) (9026.9313 4242.5496) (9027.4809 4247.0687)
      (9028.5038 4249.0687) (9030.6412 4248.3664) (9034.229 4245.5725) (9039.0687 4241.8931) (9044.4427 4238.7634)
      (9049.2824 4237.374) (9052.5496 4238.3359) (9053.5267 4241.6031) (9052.1221 4246.458) (9048.9924 4251.8168)
      (9045.313 4256.6565) (9042.5191 4260.2443) (9041.8168 4262.3817) (9043.8321 4263.4046) (9048.3359 4263.9695)
      (9054.3664 4264.7939) (9060.3817 4266.3664) (9064.7939 4268.8092) (9066.4122 4271.8015) (9064.7939 4274.8092)
      (9060.3817 4277.2366) (9054.3664 4278.8244) (9048.3359 4279.6489) (9043.8321 4280.2137) (9041.8168 4281.2214)
      (9042.5191 4283.3588) (9045.313 4286.9466) (9048.9924 4291.7863) (9052.1221 4297.1603) (9053.5267 4302.0153)
      (9052.5496 4305.2672) (9049.2824 4306.2443) (9044.4427 4304.855) (9039.0687 4301.7099) (9034.229 4298.0458)
      (9030.6412 4295.2519) (9028.5038 4294.5496) (9027.4809 4296.5496) (9026.9313 4301.0687) (9026.1069 4307.084)
      (9024.5191 4313.0992) (9022.0763 4317.5115) (9019.084 4319.1298) (9016.0916 4317.5115) (9013.6489 4313.0992)
      (9012.0611 4307.084) (9011.2519 4301.0687) (9010.687 4296.5496) (9009.6641 4294.5496) (9007.5267 4295.2519)
      (9003.9389 4298.0458) (8999.0992 4301.7099) (8993.7252 4304.855) (8988.8855 4306.2443) (8985.6183 4305.2672)
      (8984.6412 4302.0153) (8986.0458 4297.1603) (8989.1756 4291.7863) (8992.855 4286.9466) (8995.6489 4283.3588)
      (8996.3511 4281.2214) (8994.3359 4280.2137) (8989.8321 4279.6489) (8983.8015 4278.8244) (8977.7863 4277.2366)
      (8973.374 4274.8092)
    ))
    ; P2608 -- see feature_dimensions_mm.csv
    ("06_ORNAMENT" 1 (
      (8971.7557 3981.7252) (8973.374 3978.7328) (8977.7863 3976.2901) (8983.8015 3974.7176) (8989.8321 3973.8931)
      (8994.3359 3973.3282) (8996.3511 3972.3053) (8995.6489 3970.1679) (8992.855 3966.5802) (8989.1756 3961.7405)
      (8986.0458 3956.3817) (8984.6412 3951.5267) (8985.6183 3948.2595) (8988.8855 3947.2977) (8993.7252 3948.687)
      (8999.0992 3951.8168) (9003.9389 3955.4962) (9007.5267 3958.2901) (9009.6641 3958.9924) (9010.687 3956.9924)
      (9011.2519 3952.4733) (9012.0611 3946.458) (9013.6489 3940.4427) (9016.0916 3936.0153) (9019.084 3934.3969)
      (9022.0763 3936.0153) (9024.5191 3940.4427) (9026.1069 3946.458) (9026.9313 3952.4733) (9027.4809 3956.9924)
      (9028.5038 3958.9924) (9030.6412 3958.2901) (9034.229 3955.4962) (9039.0687 3951.8168) (9044.4427 3948.687)
      (9049.2824 3947.2977) (9052.5496 3948.2595) (9053.5267 3951.5267) (9052.1221 3956.3817) (9048.9924 3961.7405)
      (9045.313 3966.5802) (9042.5191 3970.1679) (9041.8168 3972.3053) (9043.8321 3973.3282) (9048.3359 3973.8931)
      (9054.3664 3974.7176) (9060.3817 3976.2901) (9064.7939 3978.7328) (9066.4122 3981.7252) (9064.7939 3984.7328)
      (9060.3817 3987.1603) (9054.3664 3988.7481) (9048.3359 3989.5725) (9043.8321 3990.1374) (9041.8168 3991.145)
      (9042.5191 3993.2824) (9045.313 3996.8702) (9048.9924 4001.7099) (9052.1221 4007.084) (9053.5267 4011.9389)
      (9052.5496 4015.1908) (9049.2824 4016.1679) (9044.4427 4014.7786) (9039.0687 4011.6336) (9034.229 4007.9695)
      (9030.6412 4005.1756) (9028.5038 4004.4733) (9027.4809 4006.4733) (9026.9313 4010.9924) (9026.1069 4017.0076)
      (9024.5191 4023.0229) (9022.0763 4027.4351) (9019.084 4029.0534) (9016.0916 4027.4351) (9013.6489 4023.0229)
      (9012.0611 4017.0076) (9011.2519 4010.9924) (9010.687 4006.4733) (9009.6641 4004.4733) (9007.5267 4005.1756)
      (9003.9389 4007.9695) (8999.0992 4011.6336) (8993.7252 4014.7786) (8988.8855 4016.1679) (8985.6183 4015.1908)
      (8984.6412 4011.9389) (8986.0458 4007.084) (8989.1756 4001.7099) (8992.855 3996.8702) (8995.6489 3993.2824)
      (8996.3511 3991.145) (8994.3359 3990.1374) (8989.8321 3989.5725) (8983.8015 3988.7481) (8977.7863 3987.1603)
      (8973.374 3984.7328)
    ))
    ; P2609 -- see feature_dimensions_mm.csv
    ("06_ORNAMENT" 1 (
      (8980.2901 2946.9771) (8980.5802 2930.5038) (8982.2748 2914.0) (8985.4656 2897.6947) (8990.1679 2881.8168)
      (8996.458 2866.626) (9004.3817 2852.3359) (9013.9847 2839.2214) (9025.3282 2827.4809) (9038.458 2817.3893)
      (9053.4351 2809.1603) (9060.9466 2825.1908) (9065.8931 2841.6794) (9068.4733 2858.4122) (9068.8702 2875.2214)
      (9067.2672 2891.9389) (9063.8168 2908.3511) (9058.7328 2924.3053) (9052.1832 2939.6183) (9044.3664 2954.0916)
      (9035.4351 2967.5573) (9025.5878 2979.8168) (9015.0076 2990.7023) (9003.8779 3000.0458) (8992.3664 3007.6336)
      (8987.4656 2993.7252) (8983.8015 2978.8244) (8981.3893 2963.1603)
    ))
    ; P2610 -- see feature_dimensions_mm.csv
    ("06_ORNAMENT" 1 (
      (9007.1756 5142.0305) (9008.0763 5137.4809) (9010.6565 5133.6183) (9014.5344 5131.0382) (9019.084 5130.1221)
      (9023.6336 5131.0382) (9027.5115 5133.6183) (9030.0916 5137.4809) (9030.9924 5142.0305) (9030.0916 5146.5954)
      (9027.5115 5150.458) (9023.6336 5153.0382) (9019.084 5153.9389) (9014.5344 5153.0382) (9010.6565 5150.458)
      (9008.0763 5146.5954)
    ))
    ; P2611 -- see feature_dimensions_mm.csv
    ("06_ORNAMENT" 1 (
      (9007.1756 4851.9542) (9008.0763 4847.4046) (9010.6565 4843.542) (9014.5344 4840.9618) (9019.084 4840.0458)
      (9023.6336 4840.9618) (9027.5115 4843.542) (9030.0916 4847.4046) (9030.9924 4851.9542) (9030.0916 4856.5191)
      (9027.5115 4860.3817) (9023.6336 4862.9618) (9019.084 4863.8626) (9014.5344 4862.9618) (9010.6565 4860.3817)
      (9008.0763 4856.5191)
    ))
    ; P2612 -- see feature_dimensions_mm.csv
    ("06_ORNAMENT" 1 (
      (9007.1756 4561.8779) (9008.0763 4557.3282) (9010.6565 4553.4656) (9014.5344 4550.8855) (9019.084 4549.9695)
      (9023.6336 4550.8855) (9027.5115 4553.4656) (9030.0916 4557.3282) (9030.9924 4561.8779) (9030.0916 4566.4427)
      (9027.5115 4570.3053) (9023.6336 4572.8855) (9019.084 4573.7863) (9014.5344 4572.8855) (9010.6565 4570.3053)
      (9008.0763 4566.4427)
    ))
    ; P2613 -- see feature_dimensions_mm.csv
    ("06_ORNAMENT" 1 (
      (9007.1756 4271.8015) (9008.0763 4267.2519) (9010.6565 4263.3893) (9014.5344 4260.8092) (9019.084 4259.8931)
      (9023.6336 4260.8092) (9027.5115 4263.3893) (9030.0916 4267.2519) (9030.9924 4271.8015) (9030.0916 4276.3664)
      (9027.5115 4280.229) (9023.6336 4282.8092) (9019.084 4283.7099) (9014.5344 4282.8092) (9010.6565 4280.229)
      (9008.0763 4276.3664)
    ))
    ; P2614 -- see feature_dimensions_mm.csv
    ("06_ORNAMENT" 1 (
      (9007.1756 3981.7252) (9008.0763 3977.1756) (9010.6565 3973.313) (9014.5344 3970.7328) (9019.084 3969.8168)
      (9023.6336 3970.7328) (9027.5115 3973.313) (9030.0916 3977.1756) (9030.9924 3981.7252) (9030.0916 3986.2901)
      (9027.5115 3990.1527) (9023.6336 3992.7328) (9019.084 3993.6336) (9014.5344 3992.7328) (9010.6565 3990.1527)
      (9008.0763 3986.2901)
    ))
    ; P2615 -- see feature_dimensions_mm.csv
    ("06_ORNAMENT" 1 (
      (9022.9008 7389.313) (9083.9695 7358.7786) (9145.0382 7389.313) (9083.9695 7419.8473)
    ))
    ; P2616 -- see feature_dimensions_mm.csv
    ("06_ORNAMENT" 1 (
      (9022.9008 7297.7099) (9083.9695 7267.1756) (9145.0382 7297.7099) (9083.9695 7328.2443)
    ))
    ; P2617 -- see feature_dimensions_mm.csv
    ("06_ORNAMENT" 1 (
      (9022.9008 7206.1069) (9083.9695 7175.5725) (9145.0382 7206.1069) (9083.9695 7236.6412)
    ))
    ; P2618 -- see feature_dimensions_mm.csv
    ("06_ORNAMENT" 1 (
      (9044.2748 5287.0687) (9045.8931 5284.0763) (9050.3053 5281.6336) (9056.3206 5280.0611) (9062.3511 5279.2366)
      (9066.855 5278.6718) (9068.8702 5277.6489) (9068.1679 5275.5115) (9065.374 5271.9237) (9061.6947 5267.084)
      (9058.5649 5261.7252) (9057.1603 5256.8702) (9058.1374 5253.6031) (9061.4046 5252.6412) (9066.2443 5254.0305)
      (9071.6183 5257.1603) (9076.458 5260.8397) (9080.0458 5263.6336) (9082.1832 5264.3359) (9083.2061 5262.3359)
      (9083.771 5257.8168) (9084.5802 5251.8015) (9086.1679 5245.7863) (9088.6107 5241.3588) (9091.6031 5239.7405)
      (9094.5954 5241.3588) (9097.0382 5245.7863) (9098.626 5251.8015) (9099.4504 5257.8168) (9100.0 5262.3359)
      (9101.0229 5264.3359) (9103.1603 5263.6336) (9106.7481 5260.8397) (9111.5878 5257.1603) (9116.9618 5254.0305)
      (9121.8015 5252.6412) (9125.0687 5253.6031) (9126.0458 5256.8702) (9124.6412 5261.7252) (9121.5115 5267.084)
      (9117.8321 5271.9237) (9115.0382 5275.5115) (9114.3359 5277.6489) (9116.3511 5278.6718) (9120.855 5279.2366)
      (9126.8855 5280.0611) (9132.9008 5281.6336) (9137.313 5284.0763) (9138.9313 5287.0687) (9137.313 5290.0763)
      (9132.9008 5292.5038) (9126.8855 5294.0916) (9120.855 5294.916) (9116.3511 5295.4809) (9114.3359 5296.4885)
      (9115.0382 5298.626) (9117.8321 5302.2137) (9121.5115 5307.0534) (9124.6412 5312.4275) (9126.0458 5317.2824)
      (9125.0687 5320.5344) (9121.8015 5321.5115) (9116.9618 5320.1221) (9111.5878 5316.9771) (9106.7481 5313.313)
      (9103.1603 5310.5191) (9101.0229 5309.8168) (9100.0 5311.8168) (9099.4504 5316.3359) (9098.626 5322.3511)
      (9097.0382 5328.3664) (9094.5954 5332.7786) (9091.6031 5334.3969) (9088.6107 5332.7786) (9086.1679 5328.3664)
      (9084.5802 5322.3511) (9083.771 5316.3359) (9083.2061 5311.8168) (9082.1832 5309.8168) (9080.0458 5310.5191)
      (9076.458 5313.313) (9071.6183 5316.9771) (9066.2443 5320.1221) (9061.4046 5321.5115) (9058.1374 5320.5344)
      (9057.1603 5317.2824) (9058.5649 5312.4275) (9061.6947 5307.0534) (9065.374 5302.2137) (9068.1679 5298.626)
      (9068.8702 5296.4885) (9066.855 5295.4809) (9062.3511 5294.916) (9056.3206 5294.0916) (9050.3053 5292.5038)
      (9045.8931 5290.0763)
    ))
    ; P2619 -- see feature_dimensions_mm.csv
    ("06_ORNAMENT" 1 (
      (9044.2748 4996.9924) (9045.8931 4994.0) (9050.3053 4991.5573) (9056.3206 4989.9847) (9062.3511 4989.1603)
      (9066.855 4988.5954) (9068.8702 4987.5725) (9068.1679 4985.4351) (9065.374 4981.8473) (9061.6947 4977.0076)
      (9058.5649 4971.6489) (9057.1603 4966.7939) (9058.1374 4963.5267) (9061.4046 4962.5649) (9066.2443 4963.9542)
      (9071.6183 4967.084) (9076.458 4970.7634) (9080.0458 4973.5573) (9082.1832 4974.2595) (9083.2061 4972.2595)
      (9083.771 4967.7405) (9084.5802 4961.7252) (9086.1679 4955.7099) (9088.6107 4951.2824) (9091.6031 4949.6641)
      (9094.5954 4951.2824) (9097.0382 4955.7099) (9098.626 4961.7252) (9099.4504 4967.7405) (9100.0 4972.2595)
      (9101.0229 4974.2595) (9103.1603 4973.5573) (9106.7481 4970.7634) (9111.5878 4967.084) (9116.9618 4963.9542)
      (9121.8015 4962.5649) (9125.0687 4963.5267) (9126.0458 4966.7939) (9124.6412 4971.6489) (9121.5115 4977.0076)
      (9117.8321 4981.8473) (9115.0382 4985.4351) (9114.3359 4987.5725) (9116.3511 4988.5954) (9120.855 4989.1603)
      (9126.8855 4989.9847) (9132.9008 4991.5573) (9137.313 4994.0) (9138.9313 4996.9924) (9137.313 5000.0)
      (9132.9008 5002.4275) (9126.8855 5004.0153) (9120.855 5004.8397) (9116.3511 5005.4046) (9114.3359 5006.4122)
      (9115.0382 5008.5496) (9117.8321 5012.1374) (9121.5115 5016.9771) (9124.6412 5022.3511) (9126.0458 5027.2061)
      (9125.0687 5030.458) (9121.8015 5031.4351) (9116.9618 5030.0458) (9111.5878 5026.9008) (9106.7481 5023.2366)
      (9103.1603 5020.4427) (9101.0229 5019.7405) (9100.0 5021.7405) (9099.4504 5026.2595) (9098.626 5032.2748)
      (9097.0382 5038.2901) (9094.5954 5042.7023) (9091.6031 5044.3206) (9088.6107 5042.7023) (9086.1679 5038.2901)
      (9084.5802 5032.2748) (9083.771 5026.2595) (9083.2061 5021.7405) (9082.1832 5019.7405) (9080.0458 5020.4427)
      (9076.458 5023.2366) (9071.6183 5026.9008) (9066.2443 5030.0458) (9061.4046 5031.4351) (9058.1374 5030.458)
      (9057.1603 5027.2061) (9058.5649 5022.3511) (9061.6947 5016.9771) (9065.374 5012.1374) (9068.1679 5008.5496)
      (9068.8702 5006.4122) (9066.855 5005.4046) (9062.3511 5004.8397) (9056.3206 5004.0153) (9050.3053 5002.4275)
      (9045.8931 5000.0)
    ))
    ; P2620 -- see feature_dimensions_mm.csv
    ("06_ORNAMENT" 1 (
      (9044.2748 4706.916) (9045.8931 4703.9237) (9050.3053 4701.4809) (9056.3206 4699.9084) (9062.3511 4699.084)
      (9066.855 4698.5191) (9068.8702 4697.4962) (9068.1679 4695.3588) (9065.374 4691.771) (9061.6947 4686.9313)
      (9058.5649 4681.5725) (9057.1603 4676.7176) (9058.1374 4673.4504) (9061.4046 4672.4885) (9066.2443 4673.8779)
      (9071.6183 4677.0076) (9076.458 4680.687) (9080.0458 4683.4809) (9082.1832 4684.1832) (9083.2061 4682.1832)
      (9083.771 4677.6641) (9084.5802 4671.6489) (9086.1679 4665.6336) (9088.6107 4661.2061) (9091.6031 4659.5878)
      (9094.5954 4661.2061) (9097.0382 4665.6336) (9098.626 4671.6489) (9099.4504 4677.6641) (9100.0 4682.1832)
      (9101.0229 4684.1832) (9103.1603 4683.4809) (9106.7481 4680.687) (9111.5878 4677.0076) (9116.9618 4673.8779)
      (9121.8015 4672.4885) (9125.0687 4673.4504) (9126.0458 4676.7176) (9124.6412 4681.5725) (9121.5115 4686.9313)
      (9117.8321 4691.771) (9115.0382 4695.3588) (9114.3359 4697.4962) (9116.3511 4698.5191) (9120.855 4699.084)
      (9126.8855 4699.9084) (9132.9008 4701.4809) (9137.313 4703.9237) (9138.9313 4706.916) (9137.313 4709.9237)
      (9132.9008 4712.3511) (9126.8855 4713.9389) (9120.855 4714.7634) (9116.3511 4715.3282) (9114.3359 4716.3359)
      (9115.0382 4718.4733) (9117.8321 4722.0611) (9121.5115 4726.9008) (9124.6412 4732.2748) (9126.0458 4737.1298)
      (9125.0687 4740.3817) (9121.8015 4741.3588) (9116.9618 4739.9695) (9111.5878 4736.8244) (9106.7481 4733.1603)
      (9103.1603 4730.3664) (9101.0229 4729.6641) (9100.0 4731.6641) (9099.4504 4736.1832) (9098.626 4742.1985)
      (9097.0382 4748.2137) (9094.5954 4752.626) (9091.6031 4754.2443) (9088.6107 4752.626) (9086.1679 4748.2137)
      (9084.5802 4742.1985) (9083.771 4736.1832) (9083.2061 4731.6641) (9082.1832 4729.6641) (9080.0458 4730.3664)
      (9076.458 4733.1603) (9071.6183 4736.8244) (9066.2443 4739.9695) (9061.4046 4741.3588) (9058.1374 4740.3817)
      (9057.1603 4737.1298) (9058.5649 4732.2748) (9061.6947 4726.9008) (9065.374 4722.0611) (9068.1679 4718.4733)
      (9068.8702 4716.3359) (9066.855 4715.3282) (9062.3511 4714.7634) (9056.3206 4713.9389) (9050.3053 4712.3511)
      (9045.8931 4709.9237)
    ))
    ; P2621 -- see feature_dimensions_mm.csv
    ("06_ORNAMENT" 1 (
      (9044.2748 4126.7634) (9045.8931 4123.771) (9050.3053 4121.3282) (9056.3206 4119.7557) (9062.3511 4118.9313)
      (9066.855 4118.3664) (9068.8702 4117.3435) (9068.1679 4115.2061) (9065.374 4111.6183) (9061.6947 4106.7786)
      (9058.5649 4101.4198) (9057.1603 4096.5649) (9058.1374 4093.2977) (9061.4046 4092.3359) (9066.2443 4093.7252)
      (9071.6183 4096.855) (9076.458 4100.5344) (9080.0458 4103.3282) (9082.1832 4104.0305) (9083.2061 4102.0305)
      (9083.771 4097.5115) (9084.5802 4091.4962) (9086.1679 4085.4809) (9088.6107 4081.0534) (9091.6031 4079.4351)
      (9094.5954 4081.0534) (9097.0382 4085.4809) (9098.626 4091.4962) (9099.4504 4097.5115) (9100.0 4102.0305)
      (9101.0229 4104.0305) (9103.1603 4103.3282) (9106.7481 4100.5344) (9111.5878 4096.855) (9116.9618 4093.7252)
      (9121.8015 4092.3359) (9125.0687 4093.2977) (9126.0458 4096.5649) (9124.6412 4101.4198) (9121.5115 4106.7786)
      (9117.8321 4111.6183) (9115.0382 4115.2061) (9114.3359 4117.3435) (9116.3511 4118.3664) (9120.855 4118.9313)
      (9126.8855 4119.7557) (9132.9008 4121.3282) (9137.313 4123.771) (9138.9313 4126.7634) (9137.313 4129.771)
      (9132.9008 4132.1985) (9126.8855 4133.7863) (9120.855 4134.6107) (9116.3511 4135.1756) (9114.3359 4136.1832)
      (9115.0382 4138.3206) (9117.8321 4141.9084) (9121.5115 4146.7481) (9124.6412 4152.1221) (9126.0458 4156.9771)
      (9125.0687 4160.229) (9121.8015 4161.2061) (9116.9618 4159.8168) (9111.5878 4156.6718) (9106.7481 4153.0076)
      (9103.1603 4150.2137) (9101.0229 4149.5115) (9100.0 4151.5115) (9099.4504 4156.0305) (9098.626 4162.0458)
      (9097.0382 4168.0611) (9094.5954 4172.4733) (9091.6031 4174.0916) (9088.6107 4172.4733) (9086.1679 4168.0611)
      (9084.5802 4162.0458) (9083.771 4156.0305) (9083.2061 4151.5115) (9082.1832 4149.5115) (9080.0458 4150.2137)
      (9076.458 4153.0076) (9071.6183 4156.6718) (9066.2443 4159.8168) (9061.4046 4161.2061) (9058.1374 4160.229)
      (9057.1603 4156.9771) (9058.5649 4152.1221) (9061.6947 4146.7481) (9065.374 4141.9084) (9068.1679 4138.3206)
      (9068.8702 4136.1832) (9066.855 4135.1756) (9062.3511 4134.6107) (9056.3206 4133.7863) (9050.3053 4132.1985)
      (9045.8931 4129.771)
    ))
    ; P2622 -- see feature_dimensions_mm.csv
    ("06_ORNAMENT" 1 (
      (9073.2824 5069.5115) (9091.6031 5048.9008) (9109.9237 5069.5115) (9091.6031 5090.1221)
    ))
    ; P2623 -- see feature_dimensions_mm.csv
    ("06_ORNAMENT" 1 (
      (9073.2824 4779.4351) (9091.6031 4758.8244) (9109.9237 4779.4351) (9091.6031 4800.0458)
    ))
    ; P2624 -- see feature_dimensions_mm.csv
    ("06_ORNAMENT" 1 (
      (9073.2824 4199.2824) (9091.6031 4178.6718) (9109.9237 4199.2824) (9091.6031 4219.8931)
    ))
    ; P2625 -- see feature_dimensions_mm.csv
    ("06_ORNAMENT" 1 (
      (9073.2824 3909.2061) (9091.6031 3888.5954) (9109.9237 3909.2061) (9091.6031 3929.8168)
    ))
    ; P2626 -- see feature_dimensions_mm.csv
    ("06_ORNAMENT" 1 (
      (9079.6947 5287.0687) (9080.5954 5282.5191) (9083.1756 5278.6565) (9087.0534 5276.0763) (9091.6031 5275.1603)
      (9096.1527 5276.0763) (9100.0305 5278.6565) (9102.6107 5282.5191) (9103.5115 5287.0687) (9102.6107 5291.6336)
      (9100.0305 5295.4962) (9096.1527 5298.0763) (9091.6031 5298.9771) (9087.0534 5298.0763) (9083.1756 5295.4962)
      (9080.5954 5291.6336)
    ))
    ; P2627 -- see feature_dimensions_mm.csv
    ("06_ORNAMENT" 1 (
      (9079.6947 4996.9924) (9080.5954 4992.4427) (9083.1756 4988.5802) (9087.0534 4986.0) (9091.6031 4985.084)
      (9096.1527 4986.0) (9100.0305 4988.5802) (9102.6107 4992.4427) (9103.5115 4996.9924) (9102.6107 5001.5573)
      (9100.0305 5005.4198) (9096.1527 5008.0) (9091.6031 5008.9008) (9087.0534 5008.0) (9083.1756 5005.4198)
      (9080.5954 5001.5573)
    ))
    ; P2628 -- see feature_dimensions_mm.csv
    ("06_ORNAMENT" 1 (
      (9079.6947 4706.916) (9080.5954 4702.3664) (9083.1756 4698.5038) (9087.0534 4695.9237) (9091.6031 4695.0076)
      (9096.1527 4695.9237) (9100.0305 4698.5038) (9102.6107 4702.3664) (9103.5115 4706.916) (9102.6107 4711.4809)
      (9100.0305 4715.3435) (9096.1527 4717.9237) (9091.6031 4718.8244) (9087.0534 4717.9237) (9083.1756 4715.3435)
      (9080.5954 4711.4809)
    ))
    ; P2629 -- see feature_dimensions_mm.csv
    ("06_ORNAMENT" 1 (
      (9079.6947 4126.7634) (9080.5954 4122.2137) (9083.1756 4118.3511) (9087.0534 4115.771) (9091.6031 4114.855)
      (9096.1527 4115.771) (9100.0305 4118.3511) (9102.6107 4122.2137) (9103.5115 4126.7634) (9102.6107 4131.3282)
      (9100.0305 4135.1908) (9096.1527 4137.771) (9091.6031 4138.6718) (9087.0534 4137.771) (9083.1756 4135.1908)
      (9080.5954 4131.3282)
    ))
    ; P2630 -- see feature_dimensions_mm.csv
    ("06_ORNAMENT" 1 (
      (9116.7939 5142.0305) (9118.4122 5139.0382) (9122.8244 5136.5954) (9128.8397 5135.0229) (9134.8702 5134.1985)
      (9139.374 5133.6336) (9141.3893 5132.6107) (9140.687 5130.4733) (9137.8931 5126.8855) (9134.2137 5122.0458)
      (9131.084 5116.687) (9129.6794 5111.8321) (9130.6565 5108.5649) (9133.9237 5107.6031) (9138.7634 5108.9924)
      (9144.1374 5112.1221) (9148.9771 5115.8015) (9152.5649 5118.5954) (9154.7023 5119.2977) (9155.7252 5117.2977)
      (9156.2901 5112.7786) (9157.0992 5106.7634) (9158.687 5100.7481) (9161.1298 5096.3206) (9164.1221 5094.7023)
      (9167.1145 5096.3206) (9169.5573 5100.7481) (9171.145 5106.7634) (9171.9695 5112.7786) (9172.5191 5117.2977)
      (9173.542 5119.2977) (9175.6794 5118.5954) (9179.2672 5115.8015) (9184.1069 5112.1221) (9189.4809 5108.9924)
      (9194.3206 5107.6031) (9197.5878 5108.5649) (9198.5649 5111.8321) (9197.1603 5116.687) (9194.0305 5122.0458)
      (9190.3511 5126.8855) (9187.5573 5130.4733) (9186.855 5132.6107) (9188.8702 5133.6336) (9193.374 5134.1985)
      (9199.4046 5135.0229) (9205.4198 5136.5954) (9209.8321 5139.0382) (9211.4504 5142.0305) (9209.8321 5145.0382)
      (9205.4198 5147.4656) (9199.4046 5149.0534) (9193.374 5149.8779) (9188.8702 5150.4427) (9186.855 5151.4504)
      (9187.5573 5153.5878) (9190.3511 5157.1756) (9194.0305 5162.0153) (9197.1603 5167.3893) (9198.5649 5172.2443)
      (9197.5878 5175.4962) (9194.3206 5176.4733) (9189.4809 5175.084) (9184.1069 5171.9389) (9179.2672 5168.2748)
      (9175.6794 5165.4809) (9173.542 5164.7786) (9172.5191 5166.7786) (9171.9695 5171.2977) (9171.145 5177.313)
      (9169.5573 5183.3282) (9167.1145 5187.7405) (9164.1221 5189.3588) (9161.1298 5187.7405) (9158.687 5183.3282)
      (9157.0992 5177.313) (9156.2901 5171.2977) (9155.7252 5166.7786) (9154.7023 5164.7786) (9152.5649 5165.4809)
      (9148.9771 5168.2748) (9144.1374 5171.9389) (9138.7634 5175.084) (9133.9237 5176.4733) (9130.6565 5175.4962)
      (9129.6794 5172.2443) (9131.084 5167.3893) (9134.2137 5162.0153) (9137.8931 5157.1756) (9140.687 5153.5878)
      (9141.3893 5151.4504) (9139.374 5150.4427) (9134.8702 5149.8779) (9128.8397 5149.0534) (9122.8244 5147.4656)
      (9118.4122 5145.0382)
    ))
    ; P2631 -- see feature_dimensions_mm.csv
    ("06_ORNAMENT" 1 (
      (9116.7939 4851.9542) (9118.4122 4848.9618) (9122.8244 4846.5191) (9128.8397 4844.9466) (9134.8702 4844.1221)
      (9139.374 4843.5573) (9141.3893 4842.5344) (9140.687 4840.3969) (9137.8931 4836.8092) (9134.2137 4831.9695)
      (9131.084 4826.6107) (9129.6794 4821.7557) (9130.6565 4818.4885) (9133.9237 4817.5267) (9138.7634 4818.916)
      (9144.1374 4822.0458) (9148.9771 4825.7252) (9152.5649 4828.5191) (9154.7023 4829.2214) (9155.7252 4827.2214)
      (9156.2901 4822.7023) (9157.0992 4816.687) (9158.687 4810.6718) (9161.1298 4806.2443) (9164.1221 4804.626)
      (9167.1145 4806.2443) (9169.5573 4810.6718) (9171.145 4816.687) (9171.9695 4822.7023) (9172.5191 4827.2214)
      (9173.542 4829.2214) (9175.6794 4828.5191) (9179.2672 4825.7252) (9184.1069 4822.0458) (9189.4809 4818.916)
      (9194.3206 4817.5267) (9197.5878 4818.4885) (9198.5649 4821.7557) (9197.1603 4826.6107) (9194.0305 4831.9695)
      (9190.3511 4836.8092) (9187.5573 4840.3969) (9186.855 4842.5344) (9188.8702 4843.5573) (9193.374 4844.1221)
      (9199.4046 4844.9466) (9205.4198 4846.5191) (9209.8321 4848.9618) (9211.4504 4851.9542) (9209.8321 4854.9618)
      (9205.4198 4857.3893) (9199.4046 4858.9771) (9193.374 4859.8015) (9188.8702 4860.3664) (9186.855 4861.374)
      (9187.5573 4863.5115) (9190.3511 4867.0992) (9194.0305 4871.9389) (9197.1603 4877.313) (9198.5649 4882.1679)
      (9197.5878 4885.4198) (9194.3206 4886.3969) (9189.4809 4885.0076) (9184.1069 4881.8626) (9179.2672 4878.1985)
      (9175.6794 4875.4046) (9173.542 4874.7023) (9172.5191 4876.7023) (9171.9695 4881.2214) (9171.145 4887.2366)
      (9169.5573 4893.2519) (9167.1145 4897.6641) (9164.1221 4899.2824) (9161.1298 4897.6641) (9158.687 4893.2519)
      (9157.0992 4887.2366) (9156.2901 4881.2214) (9155.7252 4876.7023) (9154.7023 4874.7023) (9152.5649 4875.4046)
      (9148.9771 4878.1985) (9144.1374 4881.8626) (9138.7634 4885.0076) (9133.9237 4886.3969) (9130.6565 4885.4198)
      (9129.6794 4882.1679) (9131.084 4877.313) (9134.2137 4871.9389) (9137.8931 4867.0992) (9140.687 4863.5115)
      (9141.3893 4861.374) (9139.374 4860.3664) (9134.8702 4859.8015) (9128.8397 4858.9771) (9122.8244 4857.3893)
      (9118.4122 4854.9618)
    ))
    ; P2632 -- see feature_dimensions_mm.csv
    ("06_ORNAMENT" 1 (
      (9116.7939 4561.8779) (9118.4122 4558.8855) (9122.8244 4556.4427) (9128.8397 4554.8702) (9134.8702 4554.0458)
      (9139.374 4553.4809) (9141.3893 4552.458) (9140.687 4550.3206) (9137.8931 4546.7328) (9134.2137 4541.8931)
      (9131.084 4536.5344) (9129.6794 4531.6794) (9130.6565 4528.4122) (9133.9237 4527.4504) (9138.7634 4528.8397)
      (9144.1374 4531.9695) (9148.9771 4535.6489) (9152.5649 4538.4427) (9154.7023 4539.145) (9155.7252 4537.145)
      (9156.2901 4532.626) (9157.0992 4526.6107) (9158.687 4520.5954) (9161.1298 4516.1679) (9164.1221 4514.5496)
      (9167.1145 4516.1679) (9169.5573 4520.5954) (9171.145 4526.6107) (9171.9695 4532.626) (9172.5191 4537.145)
      (9173.542 4539.145) (9175.6794 4538.4427) (9179.2672 4535.6489) (9184.1069 4531.9695) (9189.4809 4528.8397)
      (9194.3206 4527.4504) (9197.5878 4528.4122) (9198.5649 4531.6794) (9197.1603 4536.5344) (9194.0305 4541.8931)
      (9190.3511 4546.7328) (9187.5573 4550.3206) (9186.855 4552.458) (9188.8702 4553.4809) (9193.374 4554.0458)
      (9199.4046 4554.8702) (9205.4198 4556.4427) (9209.8321 4558.8855) (9211.4504 4561.8779) (9209.8321 4564.8855)
      (9205.4198 4567.313) (9199.4046 4568.9008) (9193.374 4569.7252) (9188.8702 4570.2901) (9186.855 4571.2977)
      (9187.5573 4573.4351) (9190.3511 4577.0229) (9194.0305 4581.8626) (9197.1603 4587.2366) (9198.5649 4592.0916)
      (9197.5878 4595.3435) (9194.3206 4596.3206) (9189.4809 4594.9313) (9184.1069 4591.7863) (9179.2672 4588.1221)
      (9175.6794 4585.3282) (9173.542 4584.626) (9172.5191 4586.626) (9171.9695 4591.145) (9171.145 4597.1603)
      (9169.5573 4603.1756) (9167.1145 4607.5878) (9164.1221 4609.2061) (9161.1298 4607.5878) (9158.687 4603.1756)
      (9157.0992 4597.1603) (9156.2901 4591.145) (9155.7252 4586.626) (9154.7023 4584.626) (9152.5649 4585.3282)
      (9148.9771 4588.1221) (9144.1374 4591.7863) (9138.7634 4594.9313) (9133.9237 4596.3206) (9130.6565 4595.3435)
      (9129.6794 4592.0916) (9131.084 4587.2366) (9134.2137 4581.8626) (9137.8931 4577.0229) (9140.687 4573.4351)
      (9141.3893 4571.2977) (9139.374 4570.2901) (9134.8702 4569.7252) (9128.8397 4568.9008) (9122.8244 4567.313)
      (9118.4122 4564.8855)
    ))
    ; P2633 -- see feature_dimensions_mm.csv
    ("06_ORNAMENT" 1 (
      (9116.7939 4271.8015) (9118.4122 4268.8092) (9122.8244 4266.3664) (9128.8397 4264.7939) (9134.8702 4263.9695)
      (9139.374 4263.4046) (9141.3893 4262.3817) (9140.687 4260.2443) (9137.8931 4256.6565) (9134.2137 4251.8168)
      (9131.084 4246.458) (9129.6794 4241.6031) (9130.6565 4238.3359) (9133.9237 4237.374) (9138.7634 4238.7634)
      (9144.1374 4241.8931) (9148.9771 4245.5725) (9152.5649 4248.3664) (9154.7023 4249.0687) (9155.7252 4247.0687)
      (9156.2901 4242.5496) (9157.0992 4236.5344) (9158.687 4230.5191) (9161.1298 4226.0916) (9164.1221 4224.4733)
      (9167.1145 4226.0916) (9169.5573 4230.5191) (9171.145 4236.5344) (9171.9695 4242.5496) (9172.5191 4247.0687)
      (9173.542 4249.0687) (9175.6794 4248.3664) (9179.2672 4245.5725) (9184.1069 4241.8931) (9189.4809 4238.7634)
      (9194.3206 4237.374) (9197.5878 4238.3359) (9198.5649 4241.6031) (9197.1603 4246.458) (9194.0305 4251.8168)
      (9190.3511 4256.6565) (9187.5573 4260.2443) (9186.855 4262.3817) (9188.8702 4263.4046) (9193.374 4263.9695)
      (9199.4046 4264.7939) (9205.4198 4266.3664) (9209.8321 4268.8092) (9211.4504 4271.8015) (9209.8321 4274.8092)
      (9205.4198 4277.2366) (9199.4046 4278.8244) (9193.374 4279.6489) (9188.8702 4280.2137) (9186.855 4281.2214)
      (9187.5573 4283.3588) (9190.3511 4286.9466) (9194.0305 4291.7863) (9197.1603 4297.1603) (9198.5649 4302.0153)
      (9197.5878 4305.2672) (9194.3206 4306.2443) (9189.4809 4304.855) (9184.1069 4301.7099) (9179.2672 4298.0458)
      (9175.6794 4295.2519) (9173.542 4294.5496) (9172.5191 4296.5496) (9171.9695 4301.0687) (9171.145 4307.084)
      (9169.5573 4313.0992) (9167.1145 4317.5115) (9164.1221 4319.1298) (9161.1298 4317.5115) (9158.687 4313.0992)
      (9157.0992 4307.084) (9156.2901 4301.0687) (9155.7252 4296.5496) (9154.7023 4294.5496) (9152.5649 4295.2519)
      (9148.9771 4298.0458) (9144.1374 4301.7099) (9138.7634 4304.855) (9133.9237 4306.2443) (9130.6565 4305.2672)
      (9129.6794 4302.0153) (9131.084 4297.1603) (9134.2137 4291.7863) (9137.8931 4286.9466) (9140.687 4283.3588)
      (9141.3893 4281.2214) (9139.374 4280.2137) (9134.8702 4279.6489) (9128.8397 4278.8244) (9122.8244 4277.2366)
      (9118.4122 4274.8092)
    ))
    ; P2634 -- see feature_dimensions_mm.csv
    ("06_ORNAMENT" 1 (
      (9116.7939 3981.7252) (9118.4122 3978.7328) (9122.8244 3976.2901) (9128.8397 3974.7176) (9134.8702 3973.8931)
      (9139.374 3973.3282) (9141.3893 3972.3053) (9140.687 3970.1679) (9137.8931 3966.5802) (9134.2137 3961.7405)
      (9131.084 3956.3817) (9129.6794 3951.5267) (9130.6565 3948.2595) (9133.9237 3947.2977) (9138.7634 3948.687)
      (9144.1374 3951.8168) (9148.9771 3955.4962) (9152.5649 3958.2901) (9154.7023 3958.9924) (9155.7252 3956.9924)
      (9156.2901 3952.4733) (9157.0992 3946.458) (9158.687 3940.4427) (9161.1298 3936.0153) (9164.1221 3934.3969)
      (9167.1145 3936.0153) (9169.5573 3940.4427) (9171.145 3946.458) (9171.9695 3952.4733) (9172.5191 3956.9924)
      (9173.542 3958.9924) (9175.6794 3958.2901) (9179.2672 3955.4962) (9184.1069 3951.8168) (9189.4809 3948.687)
      (9194.3206 3947.2977) (9197.5878 3948.2595) (9198.5649 3951.5267) (9197.1603 3956.3817) (9194.0305 3961.7405)
      (9190.3511 3966.5802) (9187.5573 3970.1679) (9186.855 3972.3053) (9188.8702 3973.3282) (9193.374 3973.8931)
      (9199.4046 3974.7176) (9205.4198 3976.2901) (9209.8321 3978.7328) (9211.4504 3981.7252) (9209.8321 3984.7328)
      (9205.4198 3987.1603) (9199.4046 3988.7481) (9193.374 3989.5725) (9188.8702 3990.1374) (9186.855 3991.145)
      (9187.5573 3993.2824) (9190.3511 3996.8702) (9194.0305 4001.7099) (9197.1603 4007.084) (9198.5649 4011.9389)
      (9197.5878 4015.1908) (9194.3206 4016.1679) (9189.4809 4014.7786) (9184.1069 4011.6336) (9179.2672 4007.9695)
      (9175.6794 4005.1756) (9173.542 4004.4733) (9172.5191 4006.4733) (9171.9695 4010.9924) (9171.145 4017.0076)
      (9169.5573 4023.0229) (9167.1145 4027.4351) (9164.1221 4029.0534) (9161.1298 4027.4351) (9158.687 4023.0229)
      (9157.0992 4017.0076) (9156.2901 4010.9924) (9155.7252 4006.4733) (9154.7023 4004.4733) (9152.5649 4005.1756)
      (9148.9771 4007.9695) (9144.1374 4011.6336) (9138.7634 4014.7786) (9133.9237 4016.1679) (9130.6565 4015.1908)
      (9129.6794 4011.9389) (9131.084 4007.084) (9134.2137 4001.7099) (9137.8931 3996.8702) (9140.687 3993.2824)
      (9141.3893 3991.145) (9139.374 3990.1374) (9134.8702 3989.5725) (9128.8397 3988.7481) (9122.8244 3987.1603)
      (9118.4122 3984.7328)
    ))
    ; P2635 -- see feature_dimensions_mm.csv
    ("06_ORNAMENT" 1 (
      (9145.8015 5214.5496) (9164.1221 5193.9389) (9182.4427 5214.5496) (9164.1221 5235.1603)
    ))
    ; P2636 -- see feature_dimensions_mm.csv
    ("06_ORNAMENT" 1 (
      (9145.8015 4924.4733) (9164.1221 4903.8626) (9182.4427 4924.4733) (9164.1221 4945.084)
    ))
    ; P2637 -- see feature_dimensions_mm.csv
    ("06_ORNAMENT" 1 (
      (9145.8015 4634.3969) (9164.1221 4613.7863) (9182.4427 4634.3969) (9164.1221 4655.0076)
    ))
    ; P2638 -- see feature_dimensions_mm.csv
    ("06_ORNAMENT" 1 (
      (9145.8015 4344.3206) (9164.1221 4323.7099) (9182.4427 4344.3206) (9164.1221 4364.9313)
    ))
    ; P2639 -- see feature_dimensions_mm.csv
    ("06_ORNAMENT" 1 (
      (9145.8015 4054.2443) (9164.1221 4033.6336) (9182.4427 4054.2443) (9164.1221 4074.855)
    ))
    ; P2640 -- see feature_dimensions_mm.csv
    ("06_ORNAMENT" 1 (
      (9152.2137 5142.0305) (9153.1145 5137.4809) (9155.6947 5133.6183) (9159.5725 5131.0382) (9164.1221 5130.1221)
      (9168.6718 5131.0382) (9172.5496 5133.6183) (9175.1298 5137.4809) (9176.0305 5142.0305) (9175.1298 5146.5954)
      (9172.5496 5150.458) (9168.6718 5153.0382) (9164.1221 5153.9389) (9159.5725 5153.0382) (9155.6947 5150.458)
      (9153.1145 5146.5954)
    ))
    ; P2641 -- see feature_dimensions_mm.csv
    ("06_ORNAMENT" 1 (
      (9152.2137 4851.9542) (9153.1145 4847.4046) (9155.6947 4843.542) (9159.5725 4840.9618) (9164.1221 4840.0458)
      (9168.6718 4840.9618) (9172.5496 4843.542) (9175.1298 4847.4046) (9176.0305 4851.9542) (9175.1298 4856.5191)
      (9172.5496 4860.3817) (9168.6718 4862.9618) (9164.1221 4863.8626) (9159.5725 4862.9618) (9155.6947 4860.3817)
      (9153.1145 4856.5191)
    ))
    ; P2642 -- see feature_dimensions_mm.csv
    ("06_ORNAMENT" 1 (
      (9152.2137 4561.8779) (9153.1145 4557.3282) (9155.6947 4553.4656) (9159.5725 4550.8855) (9164.1221 4549.9695)
      (9168.6718 4550.8855) (9172.5496 4553.4656) (9175.1298 4557.3282) (9176.0305 4561.8779) (9175.1298 4566.4427)
      (9172.5496 4570.3053) (9168.6718 4572.8855) (9164.1221 4573.7863) (9159.5725 4572.8855) (9155.6947 4570.3053)
      (9153.1145 4566.4427)
    ))
    ; P2643 -- see feature_dimensions_mm.csv
    ("06_ORNAMENT" 1 (
      (9152.2137 4271.8015) (9153.1145 4267.2519) (9155.6947 4263.3893) (9159.5725 4260.8092) (9164.1221 4259.8931)
      (9168.6718 4260.8092) (9172.5496 4263.3893) (9175.1298 4267.2519) (9176.0305 4271.8015) (9175.1298 4276.3664)
      (9172.5496 4280.229) (9168.6718 4282.8092) (9164.1221 4283.7099) (9159.5725 4282.8092) (9155.6947 4280.229)
      (9153.1145 4276.3664)
    ))
    ; P2644 -- see feature_dimensions_mm.csv
    ("06_ORNAMENT" 1 (
      (9152.2137 3981.7252) (9153.1145 3977.1756) (9155.6947 3973.313) (9159.5725 3970.7328) (9164.1221 3969.8168)
      (9168.6718 3970.7328) (9172.5496 3973.313) (9175.1298 3977.1756) (9176.0305 3981.7252) (9175.1298 3986.2901)
      (9172.5496 3990.1527) (9168.6718 3992.7328) (9164.1221 3993.6336) (9159.5725 3992.7328) (9155.6947 3990.1527)
      (9153.1145 3986.2901)
    ))
    ; P2645 -- see feature_dimensions_mm.csv
    ("06_ORNAMENT" 1 (
      (9189.313 5287.0687) (9190.9313 5284.0763) (9195.3435 5281.6336) (9201.3588 5280.0611) (9207.3893 5279.2366)
      (9211.8931 5278.6718) (9213.9084 5277.6489) (9213.2061 5275.5115) (9210.4122 5271.9237) (9206.7328 5267.084)
      (9203.6031 5261.7252) (9202.1985 5256.8702) (9203.1756 5253.6031) (9206.4427 5252.6412) (9211.2824 5254.0305)
      (9216.6565 5257.1603) (9221.4962 5260.8397) (9225.084 5263.6336) (9227.2214 5264.3359) (9228.2443 5262.3359)
      (9228.8092 5257.8168) (9229.6183 5251.8015) (9231.2061 5245.7863) (9233.6489 5241.3588) (9236.6412 5239.7405)
      (9239.6336 5241.3588) (9242.0763 5245.7863) (9243.6641 5251.8015) (9244.4885 5257.8168) (9245.0382 5262.3359)
      (9246.0611 5264.3359) (9248.1985 5263.6336) (9251.7863 5260.8397) (9256.626 5257.1603) (9262.0 5254.0305)
      (9266.8397 5252.6412) (9270.1069 5253.6031) (9271.084 5256.8702) (9269.6794 5261.7252) (9266.5496 5267.084)
      (9262.8702 5271.9237) (9260.0763 5275.5115) (9259.374 5277.6489) (9261.3893 5278.6718) (9265.8931 5279.2366)
      (9271.9237 5280.0611) (9277.9389 5281.6336) (9282.3511 5284.0763) (9283.9695 5287.0687) (9282.3511 5290.0763)
      (9277.9389 5292.5038) (9271.9237 5294.0916) (9265.8931 5294.916) (9261.3893 5295.4809) (9259.374 5296.4885)
      (9260.0763 5298.626) (9262.8702 5302.2137) (9266.5496 5307.0534) (9269.6794 5312.4275) (9271.084 5317.2824)
      (9270.1069 5320.5344) (9266.8397 5321.5115) (9262.0 5320.1221) (9256.626 5316.9771) (9251.7863 5313.313)
      (9248.1985 5310.5191) (9246.0611 5309.8168) (9245.0382 5311.8168) (9244.4885 5316.3359) (9243.6641 5322.3511)
      (9242.0763 5328.3664) (9239.6336 5332.7786) (9236.6412 5334.3969) (9233.6489 5332.7786) (9231.2061 5328.3664)
      (9229.6183 5322.3511) (9228.8092 5316.3359) (9228.2443 5311.8168) (9227.2214 5309.8168) (9225.084 5310.5191)
      (9221.4962 5313.313) (9216.6565 5316.9771) (9211.2824 5320.1221) (9206.4427 5321.5115) (9203.1756 5320.5344)
      (9202.1985 5317.2824) (9203.6031 5312.4275) (9206.7328 5307.0534) (9210.4122 5302.2137) (9213.2061 5298.626)
      (9213.9084 5296.4885) (9211.8931 5295.4809) (9207.3893 5294.916) (9201.3588 5294.0916) (9195.3435 5292.5038)
      (9190.9313 5290.0763)
    ))
    ; P2646 -- see feature_dimensions_mm.csv
    ("06_ORNAMENT" 1 (
      (9189.313 4996.9924) (9190.9313 4994.0) (9195.3435 4991.5573) (9201.3588 4989.9847) (9207.3893 4989.1603)
      (9211.8931 4988.5954) (9213.9084 4987.5725) (9213.2061 4985.4351) (9210.4122 4981.8473) (9206.7328 4977.0076)
      (9203.6031 4971.6489) (9202.1985 4966.7939) (9203.1756 4963.5267) (9206.4427 4962.5649) (9211.2824 4963.9542)
      (9216.6565 4967.084) (9221.4962 4970.7634) (9225.084 4973.5573) (9227.2214 4974.2595) (9228.2443 4972.2595)
      (9228.8092 4967.7405) (9229.6183 4961.7252) (9231.2061 4955.7099) (9233.6489 4951.2824) (9236.6412 4949.6641)
      (9239.6336 4951.2824) (9242.0763 4955.7099) (9243.6641 4961.7252) (9244.4885 4967.7405) (9245.0382 4972.2595)
      (9246.0611 4974.2595) (9248.1985 4973.5573) (9251.7863 4970.7634) (9256.626 4967.084) (9262.0 4963.9542)
      (9266.8397 4962.5649) (9270.1069 4963.5267) (9271.084 4966.7939) (9269.6794 4971.6489) (9266.5496 4977.0076)
      (9262.8702 4981.8473) (9260.0763 4985.4351) (9259.374 4987.5725) (9261.3893 4988.5954) (9265.8931 4989.1603)
      (9271.9237 4989.9847) (9277.9389 4991.5573) (9282.3511 4994.0) (9283.9695 4996.9924) (9282.3511 5000.0)
      (9277.9389 5002.4275) (9271.9237 5004.0153) (9265.8931 5004.8397) (9261.3893 5005.4046) (9259.374 5006.4122)
      (9260.0763 5008.5496) (9262.8702 5012.1374) (9266.5496 5016.9771) (9269.6794 5022.3511) (9271.084 5027.2061)
      (9270.1069 5030.458) (9266.8397 5031.4351) (9262.0 5030.0458) (9256.626 5026.9008) (9251.7863 5023.2366)
      (9248.1985 5020.4427) (9246.0611 5019.7405) (9245.0382 5021.7405) (9244.4885 5026.2595) (9243.6641 5032.2748)
      (9242.0763 5038.2901) (9239.6336 5042.7023) (9236.6412 5044.3206) (9233.6489 5042.7023) (9231.2061 5038.2901)
      (9229.6183 5032.2748) (9228.8092 5026.2595) (9228.2443 5021.7405) (9227.2214 5019.7405) (9225.084 5020.4427)
      (9221.4962 5023.2366) (9216.6565 5026.9008) (9211.2824 5030.0458) (9206.4427 5031.4351) (9203.1756 5030.458)
      (9202.1985 5027.2061) (9203.6031 5022.3511) (9206.7328 5016.9771) (9210.4122 5012.1374) (9213.2061 5008.5496)
      (9213.9084 5006.4122) (9211.8931 5005.4046) (9207.3893 5004.8397) (9201.3588 5004.0153) (9195.3435 5002.4275)
      (9190.9313 5000.0)
    ))
    ; P2647 -- see feature_dimensions_mm.csv
    ("06_ORNAMENT" 1 (
      (9189.313 4706.916) (9190.9313 4703.9237) (9195.3435 4701.4809) (9201.3588 4699.9084) (9207.3893 4699.084)
      (9211.8931 4698.5191) (9213.9084 4697.4962) (9213.2061 4695.3588) (9210.4122 4691.771) (9206.7328 4686.9313)
      (9203.6031 4681.5725) (9202.1985 4676.7176) (9203.1756 4673.4504) (9206.4427 4672.4885) (9211.2824 4673.8779)
      (9216.6565 4677.0076) (9221.4962 4680.687) (9225.084 4683.4809) (9227.2214 4684.1832) (9228.2443 4682.1832)
      (9228.8092 4677.6641) (9229.6183 4671.6489) (9231.2061 4665.6336) (9233.6489 4661.2061) (9236.6412 4659.5878)
      (9239.6336 4661.2061) (9242.0763 4665.6336) (9243.6641 4671.6489) (9244.4885 4677.6641) (9245.0382 4682.1832)
      (9246.0611 4684.1832) (9248.1985 4683.4809) (9251.7863 4680.687) (9256.626 4677.0076) (9262.0 4673.8779)
      (9266.8397 4672.4885) (9270.1069 4673.4504) (9271.084 4676.7176) (9269.6794 4681.5725) (9266.5496 4686.9313)
      (9262.8702 4691.771) (9260.0763 4695.3588) (9259.374 4697.4962) (9261.3893 4698.5191) (9265.8931 4699.084)
      (9271.9237 4699.9084) (9277.9389 4701.4809) (9282.3511 4703.9237) (9283.9695 4706.916) (9282.3511 4709.9237)
      (9277.9389 4712.3511) (9271.9237 4713.9389) (9265.8931 4714.7634) (9261.3893 4715.3282) (9259.374 4716.3359)
      (9260.0763 4718.4733) (9262.8702 4722.0611) (9266.5496 4726.9008) (9269.6794 4732.2748) (9271.084 4737.1298)
      (9270.1069 4740.3817) (9266.8397 4741.3588) (9262.0 4739.9695) (9256.626 4736.8244) (9251.7863 4733.1603)
      (9248.1985 4730.3664) (9246.0611 4729.6641) (9245.0382 4731.6641) (9244.4885 4736.1832) (9243.6641 4742.1985)
      (9242.0763 4748.2137) (9239.6336 4752.626) (9236.6412 4754.2443) (9233.6489 4752.626) (9231.2061 4748.2137)
      (9229.6183 4742.1985) (9228.8092 4736.1832) (9228.2443 4731.6641) (9227.2214 4729.6641) (9225.084 4730.3664)
      (9221.4962 4733.1603) (9216.6565 4736.8244) (9211.2824 4739.9695) (9206.4427 4741.3588) (9203.1756 4740.3817)
      (9202.1985 4737.1298) (9203.6031 4732.2748) (9206.7328 4726.9008) (9210.4122 4722.0611) (9213.2061 4718.4733)
      (9213.9084 4716.3359) (9211.8931 4715.3282) (9207.3893 4714.7634) (9201.3588 4713.9389) (9195.3435 4712.3511)
      (9190.9313 4709.9237)
    ))
    ; P2648 -- see feature_dimensions_mm.csv
    ("06_ORNAMENT" 1 (
      (9189.313 4126.7634) (9190.9313 4123.771) (9195.3435 4121.3282) (9201.3588 4119.7557) (9207.3893 4118.9313)
      (9211.8931 4118.3664) (9213.9084 4117.3435) (9213.2061 4115.2061) (9210.4122 4111.6183) (9206.7328 4106.7786)
      (9203.6031 4101.4198) (9202.1985 4096.5649) (9203.1756 4093.2977) (9206.4427 4092.3359) (9211.2824 4093.7252)
      (9216.6565 4096.855) (9221.4962 4100.5344) (9225.084 4103.3282) (9227.2214 4104.0305) (9228.2443 4102.0305)
      (9228.8092 4097.5115) (9229.6183 4091.4962) (9231.2061 4085.4809) (9233.6489 4081.0534) (9236.6412 4079.4351)
      (9239.6336 4081.0534) (9242.0763 4085.4809) (9243.6641 4091.4962) (9244.4885 4097.5115) (9245.0382 4102.0305)
      (9246.0611 4104.0305) (9248.1985 4103.3282) (9251.7863 4100.5344) (9256.626 4096.855) (9262.0 4093.7252)
      (9266.8397 4092.3359) (9270.1069 4093.2977) (9271.084 4096.5649) (9269.6794 4101.4198) (9266.5496 4106.7786)
      (9262.8702 4111.6183) (9260.0763 4115.2061) (9259.374 4117.3435) (9261.3893 4118.3664) (9265.8931 4118.9313)
      (9271.9237 4119.7557) (9277.9389 4121.3282) (9282.3511 4123.771) (9283.9695 4126.7634) (9282.3511 4129.771)
      (9277.9389 4132.1985) (9271.9237 4133.7863) (9265.8931 4134.6107) (9261.3893 4135.1756) (9259.374 4136.1832)
      (9260.0763 4138.3206) (9262.8702 4141.9084) (9266.5496 4146.7481) (9269.6794 4152.1221) (9271.084 4156.9771)
      (9270.1069 4160.229) (9266.8397 4161.2061) (9262.0 4159.8168) (9256.626 4156.6718) (9251.7863 4153.0076)
      (9248.1985 4150.2137) (9246.0611 4149.5115) (9245.0382 4151.5115) (9244.4885 4156.0305) (9243.6641 4162.0458)
      (9242.0763 4168.0611) (9239.6336 4172.4733) (9236.6412 4174.0916) (9233.6489 4172.4733) (9231.2061 4168.0611)
      (9229.6183 4162.0458) (9228.8092 4156.0305) (9228.2443 4151.5115) (9227.2214 4149.5115) (9225.084 4150.2137)
      (9221.4962 4153.0076) (9216.6565 4156.6718) (9211.2824 4159.8168) (9206.4427 4161.2061) (9203.1756 4160.229)
      (9202.1985 4156.9771) (9203.6031 4152.1221) (9206.7328 4146.7481) (9210.4122 4141.9084) (9213.2061 4138.3206)
      (9213.9084 4136.1832) (9211.8931 4135.1756) (9207.3893 4134.6107) (9201.3588 4133.7863) (9195.3435 4132.1985)
      (9190.9313 4129.771)
    ))
    ; P2649 -- see feature_dimensions_mm.csv
    ("06_ORNAMENT" 1 (
      (9218.3206 5359.5878) (9236.6412 5338.9771) (9254.9618 5359.5878) (9236.6412 5380.1985)
    ))
    ; P2650 -- see feature_dimensions_mm.csv
    ("06_ORNAMENT" 1 (
      (9218.3206 5069.5115) (9236.6412 5048.9008) (9254.9618 5069.5115) (9236.6412 5090.1221)
    ))
    ; P2651 -- see feature_dimensions_mm.csv
    ("06_ORNAMENT" 1 (
      (9218.3206 4779.4351) (9236.6412 4758.8244) (9254.9618 4779.4351) (9236.6412 4800.0458)
    ))
    ; P2652 -- see feature_dimensions_mm.csv
    ("06_ORNAMENT" 1 (
      (9218.3206 4199.2824) (9236.6412 4178.6718) (9254.9618 4199.2824) (9236.6412 4219.8931)
    ))
    ; P2653 -- see feature_dimensions_mm.csv
    ("06_ORNAMENT" 1 (
      (9218.3206 3909.2061) (9236.6412 3888.5954) (9254.9618 3909.2061) (9236.6412 3929.8168)
    ))
    ; P2654 -- see feature_dimensions_mm.csv
    ("06_ORNAMENT" 1 (
      (9224.7328 5287.0687) (9225.6336 5282.5191) (9228.2137 5278.6565) (9232.0916 5276.0763) (9236.6412 5275.1603)
      (9241.1908 5276.0763) (9245.0687 5278.6565) (9247.6489 5282.5191) (9248.5496 5287.0687) (9247.6489 5291.6336)
      (9245.0687 5295.4962) (9241.1908 5298.0763) (9236.6412 5298.9771) (9232.0916 5298.0763) (9228.2137 5295.4962)
      (9225.6336 5291.6336)
    ))
    ; P2655 -- see feature_dimensions_mm.csv
    ("06_ORNAMENT" 1 (
      (9224.7328 4996.9924) (9225.6336 4992.4427) (9228.2137 4988.5802) (9232.0916 4986.0) (9236.6412 4985.084)
      (9241.1908 4986.0) (9245.0687 4988.5802) (9247.6489 4992.4427) (9248.5496 4996.9924) (9247.6489 5001.5573)
      (9245.0687 5005.4198) (9241.1908 5008.0) (9236.6412 5008.9008) (9232.0916 5008.0) (9228.2137 5005.4198)
      (9225.6336 5001.5573)
    ))
    ; P2656 -- see feature_dimensions_mm.csv
    ("06_ORNAMENT" 1 (
      (9224.7328 4706.916) (9225.6336 4702.3664) (9228.2137 4698.5038) (9232.0916 4695.9237) (9236.6412 4695.0076)
      (9241.1908 4695.9237) (9245.0687 4698.5038) (9247.6489 4702.3664) (9248.5496 4706.916) (9247.6489 4711.4809)
      (9245.0687 4715.3435) (9241.1908 4717.9237) (9236.6412 4718.8244) (9232.0916 4717.9237) (9228.2137 4715.3435)
      (9225.6336 4711.4809)
    ))
    ; P2657 -- see feature_dimensions_mm.csv
    ("06_ORNAMENT" 1 (
      (9224.7328 4126.7634) (9225.6336 4122.2137) (9228.2137 4118.3511) (9232.0916 4115.771) (9236.6412 4114.855)
      (9241.1908 4115.771) (9245.0687 4118.3511) (9247.6489 4122.2137) (9248.5496 4126.7634) (9247.6489 4131.3282)
      (9245.0687 4135.1908) (9241.1908 4137.771) (9236.6412 4138.6718) (9232.0916 4137.771) (9228.2137 4135.1908)
      (9225.6336 4131.3282)
    ))
    ; P2658 -- see feature_dimensions_mm.csv
    ("06_ORNAMENT" 1 (
      (9261.8321 5142.0305) (9263.4504 5139.0382) (9267.8626 5136.5954) (9273.8779 5135.0229) (9279.9084 5134.1985)
      (9284.4122 5133.6336) (9286.4275 5132.6107) (9285.7252 5130.4733) (9282.9313 5126.8855) (9279.2519 5122.0458)
      (9276.1221 5116.687) (9274.7176 5111.8321) (9275.6947 5108.5649) (9278.9618 5107.6031) (9283.8015 5108.9924)
      (9289.1756 5112.1221) (9294.0153 5115.8015) (9297.6031 5118.5954) (9299.7405 5119.2977) (9300.7634 5117.2977)
      (9301.3282 5112.7786) (9302.1374 5106.7634) (9303.7252 5100.7481) (9306.1679 5096.3206) (9309.1603 5094.7023)
      (9312.1527 5096.3206) (9314.5954 5100.7481) (9316.1832 5106.7634) (9317.0076 5112.7786) (9317.5573 5117.2977)
      (9318.5802 5119.2977) (9320.7176 5118.5954) (9324.3053 5115.8015) (9329.145 5112.1221) (9334.5191 5108.9924)
      (9339.3588 5107.6031) (9342.626 5108.5649) (9343.6031 5111.8321) (9342.1985 5116.687) (9339.0687 5122.0458)
      (9335.3893 5126.8855) (9332.5954 5130.4733) (9331.8931 5132.6107) (9333.9084 5133.6336) (9338.4122 5134.1985)
      (9344.4427 5135.0229) (9350.458 5136.5954) (9354.8702 5139.0382) (9356.4885 5142.0305) (9354.8702 5145.0382)
      (9350.458 5147.4656) (9344.4427 5149.0534) (9338.4122 5149.8779) (9333.9084 5150.4427) (9331.8931 5151.4504)
      (9332.5954 5153.5878) (9335.3893 5157.1756) (9339.0687 5162.0153) (9342.1985 5167.3893) (9343.6031 5172.2443)
      (9342.626 5175.4962) (9339.3588 5176.4733) (9334.5191 5175.084) (9329.145 5171.9389) (9324.3053 5168.2748)
      (9320.7176 5165.4809) (9318.5802 5164.7786) (9317.5573 5166.7786) (9317.0076 5171.2977) (9316.1832 5177.313)
      (9314.5954 5183.3282) (9312.1527 5187.7405) (9309.1603 5189.3588) (9306.1679 5187.7405) (9303.7252 5183.3282)
      (9302.1374 5177.313) (9301.3282 5171.2977) (9300.7634 5166.7786) (9299.7405 5164.7786) (9297.6031 5165.4809)
      (9294.0153 5168.2748) (9289.1756 5171.9389) (9283.8015 5175.084) (9278.9618 5176.4733) (9275.6947 5175.4962)
      (9274.7176 5172.2443) (9276.1221 5167.3893) (9279.2519 5162.0153) (9282.9313 5157.1756) (9285.7252 5153.5878)
      (9286.4275 5151.4504) (9284.4122 5150.4427) (9279.9084 5149.8779) (9273.8779 5149.0534) (9267.8626 5147.4656)
      (9263.4504 5145.0382)
    ))
    ; P2659 -- see feature_dimensions_mm.csv
    ("06_ORNAMENT" 1 (
      (9261.8321 4851.9542) (9263.4504 4848.9618) (9267.8626 4846.5191) (9273.8779 4844.9466) (9279.9084 4844.1221)
      (9284.4122 4843.5573) (9286.4275 4842.5344) (9285.7252 4840.3969) (9282.9313 4836.8092) (9279.2519 4831.9695)
      (9276.1221 4826.6107) (9274.7176 4821.7557) (9275.6947 4818.4885) (9278.9618 4817.5267) (9283.8015 4818.916)
      (9289.1756 4822.0458) (9294.0153 4825.7252) (9297.6031 4828.5191) (9299.7405 4829.2214) (9300.7634 4827.2214)
      (9301.3282 4822.7023) (9302.1374 4816.687) (9303.7252 4810.6718) (9306.1679 4806.2443) (9309.1603 4804.626)
      (9312.1527 4806.2443) (9314.5954 4810.6718) (9316.1832 4816.687) (9317.0076 4822.7023) (9317.5573 4827.2214)
      (9318.5802 4829.2214) (9320.7176 4828.5191) (9324.3053 4825.7252) (9329.145 4822.0458) (9334.5191 4818.916)
      (9339.3588 4817.5267) (9342.626 4818.4885) (9343.6031 4821.7557) (9342.1985 4826.6107) (9339.0687 4831.9695)
      (9335.3893 4836.8092) (9332.5954 4840.3969) (9331.8931 4842.5344) (9333.9084 4843.5573) (9338.4122 4844.1221)
      (9344.4427 4844.9466) (9350.458 4846.5191) (9354.8702 4848.9618) (9356.4885 4851.9542) (9354.8702 4854.9618)
      (9350.458 4857.3893) (9344.4427 4858.9771) (9338.4122 4859.8015) (9333.9084 4860.3664) (9331.8931 4861.374)
      (9332.5954 4863.5115) (9335.3893 4867.0992) (9339.0687 4871.9389) (9342.1985 4877.313) (9343.6031 4882.1679)
      (9342.626 4885.4198) (9339.3588 4886.3969) (9334.5191 4885.0076) (9329.145 4881.8626) (9324.3053 4878.1985)
      (9320.7176 4875.4046) (9318.5802 4874.7023) (9317.5573 4876.7023) (9317.0076 4881.2214) (9316.1832 4887.2366)
      (9314.5954 4893.2519) (9312.1527 4897.6641) (9309.1603 4899.2824) (9306.1679 4897.6641) (9303.7252 4893.2519)
      (9302.1374 4887.2366) (9301.3282 4881.2214) (9300.7634 4876.7023) (9299.7405 4874.7023) (9297.6031 4875.4046)
      (9294.0153 4878.1985) (9289.1756 4881.8626) (9283.8015 4885.0076) (9278.9618 4886.3969) (9275.6947 4885.4198)
      (9274.7176 4882.1679) (9276.1221 4877.313) (9279.2519 4871.9389) (9282.9313 4867.0992) (9285.7252 4863.5115)
      (9286.4275 4861.374) (9284.4122 4860.3664) (9279.9084 4859.8015) (9273.8779 4858.9771) (9267.8626 4857.3893)
      (9263.4504 4854.9618)
    ))
    ; P2660 -- see feature_dimensions_mm.csv
    ("06_ORNAMENT" 1 (
      (9261.8321 4561.8779) (9263.4504 4558.8855) (9267.8626 4556.4427) (9273.8779 4554.8702) (9279.9084 4554.0458)
      (9284.4122 4553.4809) (9286.4275 4552.458) (9285.7252 4550.3206) (9282.9313 4546.7328) (9279.2519 4541.8931)
      (9276.1221 4536.5344) (9274.7176 4531.6794) (9275.6947 4528.4122) (9278.9618 4527.4504) (9283.8015 4528.8397)
      (9289.1756 4531.9695) (9294.0153 4535.6489) (9297.6031 4538.4427) (9299.7405 4539.145) (9300.7634 4537.145)
      (9301.3282 4532.626) (9302.1374 4526.6107) (9303.7252 4520.5954) (9306.1679 4516.1679) (9309.1603 4514.5496)
      (9312.1527 4516.1679) (9314.5954 4520.5954) (9316.1832 4526.6107) (9317.0076 4532.626) (9317.5573 4537.145)
      (9318.5802 4539.145) (9320.7176 4538.4427) (9324.3053 4535.6489) (9329.145 4531.9695) (9334.5191 4528.8397)
      (9339.3588 4527.4504) (9342.626 4528.4122) (9343.6031 4531.6794) (9342.1985 4536.5344) (9339.0687 4541.8931)
      (9335.3893 4546.7328) (9332.5954 4550.3206) (9331.8931 4552.458) (9333.9084 4553.4809) (9338.4122 4554.0458)
      (9344.4427 4554.8702) (9350.458 4556.4427) (9354.8702 4558.8855) (9356.4885 4561.8779) (9354.8702 4564.8855)
      (9350.458 4567.313) (9344.4427 4568.9008) (9338.4122 4569.7252) (9333.9084 4570.2901) (9331.8931 4571.2977)
      (9332.5954 4573.4351) (9335.3893 4577.0229) (9339.0687 4581.8626) (9342.1985 4587.2366) (9343.6031 4592.0916)
      (9342.626 4595.3435) (9339.3588 4596.3206) (9334.5191 4594.9313) (9329.145 4591.7863) (9324.3053 4588.1221)
      (9320.7176 4585.3282) (9318.5802 4584.626) (9317.5573 4586.626) (9317.0076 4591.145) (9316.1832 4597.1603)
      (9314.5954 4603.1756) (9312.1527 4607.5878) (9309.1603 4609.2061) (9306.1679 4607.5878) (9303.7252 4603.1756)
      (9302.1374 4597.1603) (9301.3282 4591.145) (9300.7634 4586.626) (9299.7405 4584.626) (9297.6031 4585.3282)
      (9294.0153 4588.1221) (9289.1756 4591.7863) (9283.8015 4594.9313) (9278.9618 4596.3206) (9275.6947 4595.3435)
      (9274.7176 4592.0916) (9276.1221 4587.2366) (9279.2519 4581.8626) (9282.9313 4577.0229) (9285.7252 4573.4351)
      (9286.4275 4571.2977) (9284.4122 4570.2901) (9279.9084 4569.7252) (9273.8779 4568.9008) (9267.8626 4567.313)
      (9263.4504 4564.8855)
    ))
    ; P2661 -- see feature_dimensions_mm.csv
    ("06_ORNAMENT" 1 (
      (9261.8321 4271.8015) (9263.4504 4268.8092) (9267.8626 4266.3664) (9273.8779 4264.7939) (9279.9084 4263.9695)
      (9284.4122 4263.4046) (9286.4275 4262.3817) (9285.7252 4260.2443) (9282.9313 4256.6565) (9279.2519 4251.8168)
      (9276.1221 4246.458) (9274.7176 4241.6031) (9275.6947 4238.3359) (9278.9618 4237.374) (9283.8015 4238.7634)
      (9289.1756 4241.8931) (9294.0153 4245.5725) (9297.6031 4248.3664) (9299.7405 4249.0687) (9300.7634 4247.0687)
      (9301.3282 4242.5496) (9302.1374 4236.5344) (9303.7252 4230.5191) (9306.1679 4226.0916) (9309.1603 4224.4733)
      (9312.1527 4226.0916) (9314.5954 4230.5191) (9316.1832 4236.5344) (9317.0076 4242.5496) (9317.5573 4247.0687)
      (9318.5802 4249.0687) (9320.7176 4248.3664) (9324.3053 4245.5725) (9329.145 4241.8931) (9334.5191 4238.7634)
      (9339.3588 4237.374) (9342.626 4238.3359) (9343.6031 4241.6031) (9342.1985 4246.458) (9339.0687 4251.8168)
      (9335.3893 4256.6565) (9332.5954 4260.2443) (9331.8931 4262.3817) (9333.9084 4263.4046) (9338.4122 4263.9695)
      (9344.4427 4264.7939) (9350.458 4266.3664) (9354.8702 4268.8092) (9356.4885 4271.8015) (9354.8702 4274.8092)
      (9350.458 4277.2366) (9344.4427 4278.8244) (9338.4122 4279.6489) (9333.9084 4280.2137) (9331.8931 4281.2214)
      (9332.5954 4283.3588) (9335.3893 4286.9466) (9339.0687 4291.7863) (9342.1985 4297.1603) (9343.6031 4302.0153)
      (9342.626 4305.2672) (9339.3588 4306.2443) (9334.5191 4304.855) (9329.145 4301.7099) (9324.3053 4298.0458)
      (9320.7176 4295.2519) (9318.5802 4294.5496) (9317.5573 4296.5496) (9317.0076 4301.0687) (9316.1832 4307.084)
      (9314.5954 4313.0992) (9312.1527 4317.5115) (9309.1603 4319.1298) (9306.1679 4317.5115) (9303.7252 4313.0992)
      (9302.1374 4307.084) (9301.3282 4301.0687) (9300.7634 4296.5496) (9299.7405 4294.5496) (9297.6031 4295.2519)
      (9294.0153 4298.0458) (9289.1756 4301.7099) (9283.8015 4304.855) (9278.9618 4306.2443) (9275.6947 4305.2672)
      (9274.7176 4302.0153) (9276.1221 4297.1603) (9279.2519 4291.7863) (9282.9313 4286.9466) (9285.7252 4283.3588)
      (9286.4275 4281.2214) (9284.4122 4280.2137) (9279.9084 4279.6489) (9273.8779 4278.8244) (9267.8626 4277.2366)
      (9263.4504 4274.8092)
    ))
    ; P2662 -- see feature_dimensions_mm.csv
    ("06_ORNAMENT" 1 (
      (9261.8321 3981.7252) (9263.4504 3978.7328) (9267.8626 3976.2901) (9273.8779 3974.7176) (9279.9084 3973.8931)
      (9284.4122 3973.3282) (9286.4275 3972.3053) (9285.7252 3970.1679) (9282.9313 3966.5802) (9279.2519 3961.7405)
      (9276.1221 3956.3817) (9274.7176 3951.5267) (9275.6947 3948.2595) (9278.9618 3947.2977) (9283.8015 3948.687)
      (9289.1756 3951.8168) (9294.0153 3955.4962) (9297.6031 3958.2901) (9299.7405 3958.9924) (9300.7634 3956.9924)
      (9301.3282 3952.4733) (9302.1374 3946.458) (9303.7252 3940.4427) (9306.1679 3936.0153) (9309.1603 3934.3969)
      (9312.1527 3936.0153) (9314.5954 3940.4427) (9316.1832 3946.458) (9317.0076 3952.4733) (9317.5573 3956.9924)
      (9318.5802 3958.9924) (9320.7176 3958.2901) (9324.3053 3955.4962) (9329.145 3951.8168) (9334.5191 3948.687)
      (9339.3588 3947.2977) (9342.626 3948.2595) (9343.6031 3951.5267) (9342.1985 3956.3817) (9339.0687 3961.7405)
      (9335.3893 3966.5802) (9332.5954 3970.1679) (9331.8931 3972.3053) (9333.9084 3973.3282) (9338.4122 3973.8931)
      (9344.4427 3974.7176) (9350.458 3976.2901) (9354.8702 3978.7328) (9356.4885 3981.7252) (9354.8702 3984.7328)
      (9350.458 3987.1603) (9344.4427 3988.7481) (9338.4122 3989.5725) (9333.9084 3990.1374) (9331.8931 3991.145)
      (9332.5954 3993.2824) (9335.3893 3996.8702) (9339.0687 4001.7099) (9342.1985 4007.084) (9343.6031 4011.9389)
      (9342.626 4015.1908) (9339.3588 4016.1679) (9334.5191 4014.7786) (9329.145 4011.6336) (9324.3053 4007.9695)
      (9320.7176 4005.1756) (9318.5802 4004.4733) (9317.5573 4006.4733) (9317.0076 4010.9924) (9316.1832 4017.0076)
      (9314.5954 4023.0229) (9312.1527 4027.4351) (9309.1603 4029.0534) (9306.1679 4027.4351) (9303.7252 4023.0229)
      (9302.1374 4017.0076) (9301.3282 4010.9924) (9300.7634 4006.4733) (9299.7405 4004.4733) (9297.6031 4005.1756)
      (9294.0153 4007.9695) (9289.1756 4011.6336) (9283.8015 4014.7786) (9278.9618 4016.1679) (9275.6947 4015.1908)
      (9274.7176 4011.9389) (9276.1221 4007.084) (9279.2519 4001.7099) (9282.9313 3996.8702) (9285.7252 3993.2824)
      (9286.4275 3991.145) (9284.4122 3990.1374) (9279.9084 3989.5725) (9273.8779 3988.7481) (9267.8626 3987.1603)
      (9263.4504 3984.7328)
    ))
    ; P2663 -- see feature_dimensions_mm.csv
    ("06_ORNAMENT" 1 (
      (9290.8397 5214.5496) (9309.1603 5193.9389) (9327.4809 5214.5496) (9309.1603 5235.1603)
    ))
    ; P2664 -- see feature_dimensions_mm.csv
    ("06_ORNAMENT" 1 (
      (9290.8397 4924.4733) (9309.1603 4903.8626) (9327.4809 4924.4733) (9309.1603 4945.084)
    ))
    ; P2665 -- see feature_dimensions_mm.csv
    ("06_ORNAMENT" 1 (
      (9290.8397 4634.3969) (9309.1603 4613.7863) (9327.4809 4634.3969) (9309.1603 4655.0076)
    ))
    ; P2666 -- see feature_dimensions_mm.csv
    ("06_ORNAMENT" 1 (
      (9290.8397 4344.3206) (9309.1603 4323.7099) (9327.4809 4344.3206) (9309.1603 4364.9313)
    ))
    ; P2667 -- see feature_dimensions_mm.csv
    ("06_ORNAMENT" 1 (
      (9290.8397 4054.2443) (9309.1603 4033.6336) (9327.4809 4054.2443) (9309.1603 4074.855)
    ))
    ; P2668 -- see feature_dimensions_mm.csv
    ("06_ORNAMENT" 1 (
      (9297.2519 5432.1069) (9298.1527 5427.5573) (9300.7328 5423.6947) (9304.6107 5421.1145) (9309.1603 5420.1985)
      (9313.7099 5421.1145) (9317.5878 5423.6947) (9320.1679 5427.5573) (9321.0687 5432.1069) (9320.1679 5436.6718)
      (9317.5878 5440.5344) (9313.7099 5443.1145) (9309.1603 5444.0153) (9304.6107 5443.1145) (9300.7328 5440.5344)
      (9298.1527 5436.6718)
    ))
    ; P2669 -- see feature_dimensions_mm.csv
    ("06_ORNAMENT" 1 (
      (9297.2519 5142.0305) (9298.1527 5137.4809) (9300.7328 5133.6183) (9304.6107 5131.0382) (9309.1603 5130.1221)
      (9313.7099 5131.0382) (9317.5878 5133.6183) (9320.1679 5137.4809) (9321.0687 5142.0305) (9320.1679 5146.5954)
      (9317.5878 5150.458) (9313.7099 5153.0382) (9309.1603 5153.9389) (9304.6107 5153.0382) (9300.7328 5150.458)
      (9298.1527 5146.5954)
    ))
    ; P2670 -- see feature_dimensions_mm.csv
    ("06_ORNAMENT" 1 (
      (9297.2519 4851.9542) (9298.1527 4847.4046) (9300.7328 4843.542) (9304.6107 4840.9618) (9309.1603 4840.0458)
      (9313.7099 4840.9618) (9317.5878 4843.542) (9320.1679 4847.4046) (9321.0687 4851.9542) (9320.1679 4856.5191)
      (9317.5878 4860.3817) (9313.7099 4862.9618) (9309.1603 4863.8626) (9304.6107 4862.9618) (9300.7328 4860.3817)
      (9298.1527 4856.5191)
    ))
    ; P2671 -- see feature_dimensions_mm.csv
    ("06_ORNAMENT" 1 (
      (9297.2519 4561.8779) (9298.1527 4557.3282) (9300.7328 4553.4656) (9304.6107 4550.8855) (9309.1603 4549.9695)
      (9313.7099 4550.8855) (9317.5878 4553.4656) (9320.1679 4557.3282) (9321.0687 4561.8779) (9320.1679 4566.4427)
      (9317.5878 4570.3053) (9313.7099 4572.8855) (9309.1603 4573.7863) (9304.6107 4572.8855) (9300.7328 4570.3053)
      (9298.1527 4566.4427)
    ))
    ; P2672 -- see feature_dimensions_mm.csv
    ("06_ORNAMENT" 1 (
      (9297.2519 4271.8015) (9298.1527 4267.2519) (9300.7328 4263.3893) (9304.6107 4260.8092) (9309.1603 4259.8931)
      (9313.7099 4260.8092) (9317.5878 4263.3893) (9320.1679 4267.2519) (9321.0687 4271.8015) (9320.1679 4276.3664)
      (9317.5878 4280.229) (9313.7099 4282.8092) (9309.1603 4283.7099) (9304.6107 4282.8092) (9300.7328 4280.229)
      (9298.1527 4276.3664)
    ))
    ; P2673 -- see feature_dimensions_mm.csv
    ("06_ORNAMENT" 1 (
      (9297.2519 3981.7252) (9298.1527 3977.1756) (9300.7328 3973.313) (9304.6107 3970.7328) (9309.1603 3969.8168)
      (9313.7099 3970.7328) (9317.5878 3973.313) (9320.1679 3977.1756) (9321.0687 3981.7252) (9320.1679 3986.2901)
      (9317.5878 3990.1527) (9313.7099 3992.7328) (9309.1603 3993.6336) (9304.6107 3992.7328) (9300.7328 3990.1527)
      (9298.1527 3986.2901)
    ))
    ; P2674 -- see feature_dimensions_mm.csv
    ("06_ORNAMENT" 1 (
      (9334.3511 5287.0687) (9335.9695 5284.0763) (9340.3817 5281.6336) (9346.3969 5280.0611) (9352.4275 5279.2366)
      (9356.9313 5278.6718) (9358.9466 5277.6489) (9358.2443 5275.5115) (9355.4504 5271.9237) (9351.771 5267.084)
      (9348.6412 5261.7252) (9347.2366 5256.8702) (9348.2137 5253.6031) (9351.4809 5252.6412) (9356.3206 5254.0305)
      (9361.6947 5257.1603) (9366.5344 5260.8397) (9370.1221 5263.6336) (9372.2595 5264.3359) (9373.2824 5262.3359)
      (9373.8473 5257.8168) (9374.6565 5251.8015) (9376.2443 5245.7863) (9378.687 5241.3588) (9381.6794 5239.7405)
      (9384.6718 5241.3588) (9387.1145 5245.7863) (9388.7023 5251.8015) (9389.5267 5257.8168) (9390.0763 5262.3359)
      (9391.0992 5264.3359) (9393.2366 5263.6336) (9396.8244 5260.8397) (9401.6641 5257.1603) (9407.0382 5254.0305)
      (9411.8779 5252.6412) (9415.145 5253.6031) (9416.1221 5256.8702) (9414.7176 5261.7252) (9411.5878 5267.084)
      (9407.9084 5271.9237) (9405.1145 5275.5115) (9404.4122 5277.6489) (9406.4275 5278.6718) (9410.9313 5279.2366)
      (9416.9618 5280.0611) (9422.9771 5281.6336) (9427.3893 5284.0763) (9429.0076 5287.0687) (9427.3893 5290.0763)
      (9422.9771 5292.5038) (9416.9618 5294.0916) (9410.9313 5294.916) (9406.4275 5295.4809) (9404.4122 5296.4885)
      (9405.1145 5298.626) (9407.9084 5302.2137) (9411.5878 5307.0534) (9414.7176 5312.4275) (9416.1221 5317.2824)
      (9415.145 5320.5344) (9411.8779 5321.5115) (9407.0382 5320.1221) (9401.6641 5316.9771) (9396.8244 5313.313)
      (9393.2366 5310.5191) (9391.0992 5309.8168) (9390.0763 5311.8168) (9389.5267 5316.3359) (9388.7023 5322.3511)
      (9387.1145 5328.3664) (9384.6718 5332.7786) (9381.6794 5334.3969) (9378.687 5332.7786) (9376.2443 5328.3664)
      (9374.6565 5322.3511) (9373.8473 5316.3359) (9373.2824 5311.8168) (9372.2595 5309.8168) (9370.1221 5310.5191)
      (9366.5344 5313.313) (9361.6947 5316.9771) (9356.3206 5320.1221) (9351.4809 5321.5115) (9348.2137 5320.5344)
      (9347.2366 5317.2824) (9348.6412 5312.4275) (9351.771 5307.0534) (9355.4504 5302.2137) (9358.2443 5298.626)
      (9358.9466 5296.4885) (9356.9313 5295.4809) (9352.4275 5294.916) (9346.3969 5294.0916) (9340.3817 5292.5038)
      (9335.9695 5290.0763)
    ))
    ; P2675 -- see feature_dimensions_mm.csv
    ("06_ORNAMENT" 1 (
      (9334.3511 4996.9924) (9335.9695 4994.0) (9340.3817 4991.5573) (9346.3969 4989.9847) (9352.4275 4989.1603)
      (9356.9313 4988.5954) (9358.9466 4987.5725) (9358.2443 4985.4351) (9355.4504 4981.8473) (9351.771 4977.0076)
      (9348.6412 4971.6489) (9347.2366 4966.7939) (9348.2137 4963.5267) (9351.4809 4962.5649) (9356.3206 4963.9542)
      (9361.6947 4967.084) (9366.5344 4970.7634) (9370.1221 4973.5573) (9372.2595 4974.2595) (9373.2824 4972.2595)
      (9373.8473 4967.7405) (9374.6565 4961.7252) (9376.2443 4955.7099) (9378.687 4951.2824) (9381.6794 4949.6641)
      (9384.6718 4951.2824) (9387.1145 4955.7099) (9388.7023 4961.7252) (9389.5267 4967.7405) (9390.0763 4972.2595)
      (9391.0992 4974.2595) (9393.2366 4973.5573) (9396.8244 4970.7634) (9401.6641 4967.084) (9407.0382 4963.9542)
      (9411.8779 4962.5649) (9415.145 4963.5267) (9416.1221 4966.7939) (9414.7176 4971.6489) (9411.5878 4977.0076)
      (9407.9084 4981.8473) (9405.1145 4985.4351) (9404.4122 4987.5725) (9406.4275 4988.5954) (9410.9313 4989.1603)
      (9416.9618 4989.9847) (9422.9771 4991.5573) (9427.3893 4994.0) (9429.0076 4996.9924) (9427.3893 5000.0)
      (9422.9771 5002.4275) (9416.9618 5004.0153) (9410.9313 5004.8397) (9406.4275 5005.4046) (9404.4122 5006.4122)
      (9405.1145 5008.5496) (9407.9084 5012.1374) (9411.5878 5016.9771) (9414.7176 5022.3511) (9416.1221 5027.2061)
      (9415.145 5030.458) (9411.8779 5031.4351) (9407.0382 5030.0458) (9401.6641 5026.9008) (9396.8244 5023.2366)
      (9393.2366 5020.4427) (9391.0992 5019.7405) (9390.0763 5021.7405) (9389.5267 5026.2595) (9388.7023 5032.2748)
      (9387.1145 5038.2901) (9384.6718 5042.7023) (9381.6794 5044.3206) (9378.687 5042.7023) (9376.2443 5038.2901)
      (9374.6565 5032.2748) (9373.8473 5026.2595) (9373.2824 5021.7405) (9372.2595 5019.7405) (9370.1221 5020.4427)
      (9366.5344 5023.2366) (9361.6947 5026.9008) (9356.3206 5030.0458) (9351.4809 5031.4351) (9348.2137 5030.458)
      (9347.2366 5027.2061) (9348.6412 5022.3511) (9351.771 5016.9771) (9355.4504 5012.1374) (9358.2443 5008.5496)
      (9358.9466 5006.4122) (9356.9313 5005.4046) (9352.4275 5004.8397) (9346.3969 5004.0153) (9340.3817 5002.4275)
      (9335.9695 5000.0)
    ))
    ; P2676 -- see feature_dimensions_mm.csv
    ("06_ORNAMENT" 1 (
      (9334.3511 4706.916) (9335.9695 4703.9237) (9340.3817 4701.4809) (9346.3969 4699.9084) (9352.4275 4699.084)
      (9356.9313 4698.5191) (9358.9466 4697.4962) (9358.2443 4695.3588) (9355.4504 4691.771) (9351.771 4686.9313)
      (9348.6412 4681.5725) (9347.2366 4676.7176) (9348.2137 4673.4504) (9351.4809 4672.4885) (9356.3206 4673.8779)
      (9361.6947 4677.0076) (9366.5344 4680.687) (9370.1221 4683.4809) (9372.2595 4684.1832) (9373.2824 4682.1832)
      (9373.8473 4677.6641) (9374.6565 4671.6489) (9376.2443 4665.6336) (9378.687 4661.2061) (9381.6794 4659.5878)
      (9384.6718 4661.2061) (9387.1145 4665.6336) (9388.7023 4671.6489) (9389.5267 4677.6641) (9390.0763 4682.1832)
      (9391.0992 4684.1832) (9393.2366 4683.4809) (9396.8244 4680.687) (9401.6641 4677.0076) (9407.0382 4673.8779)
      (9411.8779 4672.4885) (9415.145 4673.4504) (9416.1221 4676.7176) (9414.7176 4681.5725) (9411.5878 4686.9313)
      (9407.9084 4691.771) (9405.1145 4695.3588) (9404.4122 4697.4962) (9406.4275 4698.5191) (9410.9313 4699.084)
      (9416.9618 4699.9084) (9422.9771 4701.4809) (9427.3893 4703.9237) (9429.0076 4706.916) (9427.3893 4709.9237)
      (9422.9771 4712.3511) (9416.9618 4713.9389) (9410.9313 4714.7634) (9406.4275 4715.3282) (9404.4122 4716.3359)
      (9405.1145 4718.4733) (9407.9084 4722.0611) (9411.5878 4726.9008) (9414.7176 4732.2748) (9416.1221 4737.1298)
      (9415.145 4740.3817) (9411.8779 4741.3588) (9407.0382 4739.9695) (9401.6641 4736.8244) (9396.8244 4733.1603)
      (9393.2366 4730.3664) (9391.0992 4729.6641) (9390.0763 4731.6641) (9389.5267 4736.1832) (9388.7023 4742.1985)
      (9387.1145 4748.2137) (9384.6718 4752.626) (9381.6794 4754.2443) (9378.687 4752.626) (9376.2443 4748.2137)
      (9374.6565 4742.1985) (9373.8473 4736.1832) (9373.2824 4731.6641) (9372.2595 4729.6641) (9370.1221 4730.3664)
      (9366.5344 4733.1603) (9361.6947 4736.8244) (9356.3206 4739.9695) (9351.4809 4741.3588) (9348.2137 4740.3817)
      (9347.2366 4737.1298) (9348.6412 4732.2748) (9351.771 4726.9008) (9355.4504 4722.0611) (9358.2443 4718.4733)
      (9358.9466 4716.3359) (9356.9313 4715.3282) (9352.4275 4714.7634) (9346.3969 4713.9389) (9340.3817 4712.3511)
      (9335.9695 4709.9237)
    ))
    ; P2677 -- see feature_dimensions_mm.csv
    ("06_ORNAMENT" 1 (
      (9334.3511 4126.7634) (9335.9695 4123.771) (9340.3817 4121.3282) (9346.3969 4119.7557) (9352.4275 4118.9313)
      (9356.9313 4118.3664) (9358.9466 4117.3435) (9358.2443 4115.2061) (9355.4504 4111.6183) (9351.771 4106.7786)
      (9348.6412 4101.4198) (9347.2366 4096.5649) (9348.2137 4093.2977) (9351.4809 4092.3359) (9356.3206 4093.7252)
      (9361.6947 4096.855) (9366.5344 4100.5344) (9370.1221 4103.3282) (9372.2595 4104.0305) (9373.2824 4102.0305)
      (9373.8473 4097.5115) (9374.6565 4091.4962) (9376.2443 4085.4809) (9378.687 4081.0534) (9381.6794 4079.4351)
      (9384.6718 4081.0534) (9387.1145 4085.4809) (9388.7023 4091.4962) (9389.5267 4097.5115) (9390.0763 4102.0305)
      (9391.0992 4104.0305) (9393.2366 4103.3282) (9396.8244 4100.5344) (9401.6641 4096.855) (9407.0382 4093.7252)
      (9411.8779 4092.3359) (9415.145 4093.2977) (9416.1221 4096.5649) (9414.7176 4101.4198) (9411.5878 4106.7786)
      (9407.9084 4111.6183) (9405.1145 4115.2061) (9404.4122 4117.3435) (9406.4275 4118.3664) (9410.9313 4118.9313)
      (9416.9618 4119.7557) (9422.9771 4121.3282) (9427.3893 4123.771) (9429.0076 4126.7634) (9427.3893 4129.771)
      (9422.9771 4132.1985) (9416.9618 4133.7863) (9410.9313 4134.6107) (9406.4275 4135.1756) (9404.4122 4136.1832)
      (9405.1145 4138.3206) (9407.9084 4141.9084) (9411.5878 4146.7481) (9414.7176 4152.1221) (9416.1221 4156.9771)
      (9415.145 4160.229) (9411.8779 4161.2061) (9407.0382 4159.8168) (9401.6641 4156.6718) (9396.8244 4153.0076)
      (9393.2366 4150.2137) (9391.0992 4149.5115) (9390.0763 4151.5115) (9389.5267 4156.0305) (9388.7023 4162.0458)
      (9387.1145 4168.0611) (9384.6718 4172.4733) (9381.6794 4174.0916) (9378.687 4172.4733) (9376.2443 4168.0611)
      (9374.6565 4162.0458) (9373.8473 4156.0305) (9373.2824 4151.5115) (9372.2595 4149.5115) (9370.1221 4150.2137)
      (9366.5344 4153.0076) (9361.6947 4156.6718) (9356.3206 4159.8168) (9351.4809 4161.2061) (9348.2137 4160.229)
      (9347.2366 4156.9771) (9348.6412 4152.1221) (9351.771 4146.7481) (9355.4504 4141.9084) (9358.2443 4138.3206)
      (9358.9466 4136.1832) (9356.9313 4135.1756) (9352.4275 4134.6107) (9346.3969 4133.7863) (9340.3817 4132.1985)
      (9335.9695 4129.771)
    ))
    ; P2678 -- see feature_dimensions_mm.csv
    ("06_ORNAMENT" 1 (
      (9363.3588 5359.5878) (9381.6794 5338.9771) (9400.0 5359.5878) (9381.6794 5380.1985)
    ))
    ; P2679 -- see feature_dimensions_mm.csv
    ("06_ORNAMENT" 1 (
      (9363.3588 5069.5115) (9381.6794 5048.9008) (9400.0 5069.5115) (9381.6794 5090.1221)
    ))
    ; P2680 -- see feature_dimensions_mm.csv
    ("06_ORNAMENT" 1 (
      (9363.3588 4779.4351) (9381.6794 4758.8244) (9400.0 4779.4351) (9381.6794 4800.0458)
    ))
    ; P2681 -- see feature_dimensions_mm.csv
    ("06_ORNAMENT" 1 (
      (9363.3588 4199.2824) (9381.6794 4178.6718) (9400.0 4199.2824) (9381.6794 4219.8931)
    ))
    ; P2682 -- see feature_dimensions_mm.csv
    ("06_ORNAMENT" 1 (
      (9363.3588 3909.2061) (9381.6794 3888.5954) (9400.0 3909.2061) (9381.6794 3929.8168)
    ))
    ; P2683 -- see feature_dimensions_mm.csv
    ("06_ORNAMENT" 1 (
      (9369.771 5287.0687) (9370.6718 5282.5191) (9373.2519 5278.6565) (9377.1298 5276.0763) (9381.6794 5275.1603)
      (9386.229 5276.0763) (9390.1069 5278.6565) (9392.687 5282.5191) (9393.5878 5287.0687) (9392.687 5291.6336)
      (9390.1069 5295.4962) (9386.229 5298.0763) (9381.6794 5298.9771) (9377.1298 5298.0763) (9373.2519 5295.4962)
      (9370.6718 5291.6336)
    ))
    ; P2684 -- see feature_dimensions_mm.csv
    ("06_ORNAMENT" 1 (
      (9369.771 4996.9924) (9370.6718 4992.4427) (9373.2519 4988.5802) (9377.1298 4986.0) (9381.6794 4985.084)
      (9386.229 4986.0) (9390.1069 4988.5802) (9392.687 4992.4427) (9393.5878 4996.9924) (9392.687 5001.5573)
      (9390.1069 5005.4198) (9386.229 5008.0) (9381.6794 5008.9008) (9377.1298 5008.0) (9373.2519 5005.4198)
      (9370.6718 5001.5573)
    ))
    ; P2685 -- see feature_dimensions_mm.csv
    ("06_ORNAMENT" 1 (
      (9369.771 4706.916) (9370.6718 4702.3664) (9373.2519 4698.5038) (9377.1298 4695.9237) (9381.6794 4695.0076)
      (9386.229 4695.9237) (9390.1069 4698.5038) (9392.687 4702.3664) (9393.5878 4706.916) (9392.687 4711.4809)
      (9390.1069 4715.3435) (9386.229 4717.9237) (9381.6794 4718.8244) (9377.1298 4717.9237) (9373.2519 4715.3435)
      (9370.6718 4711.4809)
    ))
    ; P2686 -- see feature_dimensions_mm.csv
    ("06_ORNAMENT" 1 (
      (9369.771 4126.7634) (9370.6718 4122.2137) (9373.2519 4118.3511) (9377.1298 4115.771) (9381.6794 4114.855)
      (9386.229 4115.771) (9390.1069 4118.3511) (9392.687 4122.2137) (9393.5878 4126.7634) (9392.687 4131.3282)
      (9390.1069 4135.1908) (9386.229 4137.771) (9381.6794 4138.6718) (9377.1298 4137.771) (9373.2519 4135.1908)
      (9370.6718 4131.3282)
    ))
    ; P2687 -- see feature_dimensions_mm.csv
    ("06_ORNAMENT" 1 (
      (9435.1145 7389.313) (9496.1832 7358.7786) (9557.2519 7389.313) (9496.1832 7419.8473)
    ))
    ; P2688 -- see feature_dimensions_mm.csv
    ("06_ORNAMENT" 1 (
      (9435.1145 7297.7099) (9496.1832 7267.1756) (9557.2519 7297.7099) (9496.1832 7328.2443)
    ))
    ; P2689 -- see feature_dimensions_mm.csv
    ("06_ORNAMENT" 1 (
      (9435.1145 7206.1069) (9496.1832 7175.5725) (9557.2519 7206.1069) (9496.1832 7236.6412)
    ))
    ; P2690 -- see feature_dimensions_mm.csv
    ("06_ORNAMENT" 1 (
      (9435.8779 5214.5496) (9450.3817 5198.2443) (9450.3817 5230.8702)
    ))
    ; P2691 -- see feature_dimensions_mm.csv
    ("06_ORNAMENT" 1 (
      (9435.8779 4924.4733) (9450.3817 4908.1679) (9450.3817 4940.7939)
    ))
    ; P2692 -- see feature_dimensions_mm.csv
    ("06_ORNAMENT" 1 (
      (9435.8779 4634.3969) (9450.3817 4618.0916) (9450.3817 4650.7176)
    ))
    ; P2693 -- see feature_dimensions_mm.csv
    ("06_ORNAMENT" 1 (
      (9526.7176 5380.1985) (9526.7176 5338.9771) (9545.0382 5359.5878)
    ))
    ; P2694 -- see feature_dimensions_mm.csv
    ("06_ORNAMENT" 1 (
      (9526.7176 5090.1221) (9526.7176 5048.9008) (9545.0382 5069.5115)
    ))
    ; P2695 -- see feature_dimensions_mm.csv
    ("06_ORNAMENT" 1 (
      (9526.7176 4800.0458) (9526.7176 4758.8244) (9545.0382 4779.4351)
    ))
    ; P2696 -- see feature_dimensions_mm.csv
    ("06_ORNAMENT" 1 (
      (9526.7176 4219.8931) (9526.7176 4178.6718) (9545.0382 4199.2824)
    ))
    ; P2697 -- see feature_dimensions_mm.csv
    ("06_ORNAMENT" 1 (
      (9526.7176 3929.8168) (9526.7176 3888.5954) (9545.0382 3909.2061)
    ))
    ; P2698 -- see feature_dimensions_mm.csv
    ("06_ORNAMENT" 1 (
      (9551.9084 5432.1069) (9553.5267 5429.1145) (9557.9389 5426.6718) (9563.9542 5425.0992) (9569.9847 5424.2748)
      (9574.4885 5423.7099) (9576.5038 5422.687) (9575.8015 5420.5496) (9573.0076 5416.9618) (9569.3282 5412.1221)
      (9566.1985 5406.7634) (9564.7939 5401.9084) (9565.771 5398.6412) (9569.0382 5397.6794) (9573.8779 5399.0687)
      (9579.2519 5402.1985) (9584.0916 5405.8779) (9587.6794 5408.6718) (9589.8168 5409.374) (9590.8397 5407.374)
      (9591.4046 5402.855) (9592.2137 5396.8397) (9593.8015 5390.8244) (9596.2443 5386.3969) (9599.2366 5384.7786)
      (9602.229 5386.3969) (9604.6718 5390.8244) (9606.2595 5396.8397) (9607.084 5402.855) (9607.6336 5407.374)
      (9608.6565 5409.374) (9610.7939 5408.6718) (9614.3817 5405.8779) (9619.2214 5402.1985) (9624.5954 5399.0687)
      (9629.4351 5397.6794) (9632.7023 5398.6412) (9633.6794 5401.9084) (9632.2748 5406.7634) (9629.145 5412.1221)
      (9625.4656 5416.9618) (9622.6718 5420.5496) (9621.9695 5422.687) (9623.9847 5423.7099) (9628.4885 5424.2748)
      (9634.5191 5425.0992) (9640.5344 5426.6718) (9644.9466 5429.1145) (9646.5649 5432.1069) (9644.9466 5435.1145)
      (9640.5344 5437.542) (9634.5191 5439.1298) (9628.4885 5439.9542) (9623.9847 5440.5191) (9621.9695 5441.5267)
      (9622.6718 5443.6641) (9625.4656 5447.2519) (9629.145 5452.0916) (9632.2748 5457.4656) (9633.6794 5462.3206)
      (9632.7023 5465.5725) (9629.4351 5466.5496) (9624.5954 5465.1603) (9619.2214 5462.0153) (9614.3817 5458.3511)
      (9610.7939 5455.5573) (9608.6565 5454.855) (9607.6336 5456.855) (9607.084 5461.374) (9606.2595 5467.3893)
      (9604.6718 5473.4046) (9602.229 5477.8168) (9599.2366 5479.4351) (9596.2443 5477.8168) (9593.8015 5473.4046)
      (9592.2137 5467.3893) (9591.4046 5461.374) (9590.8397 5456.855) (9589.8168 5454.855) (9587.6794 5455.5573)
      (9584.0916 5458.3511) (9579.2519 5462.0153) (9573.8779 5465.1603) (9569.0382 5466.5496) (9565.771 5465.5725)
      (9564.7939 5462.3206) (9566.1985 5457.4656) (9569.3282 5452.0916) (9573.0076 5447.2519) (9575.8015 5443.6641)
      (9576.5038 5441.5267) (9574.4885 5440.5191) (9569.9847 5439.9542) (9563.9542 5439.1298) (9557.9389 5437.542)
      (9553.5267 5435.1145)
    ))
    ; P2699 -- see feature_dimensions_mm.csv
    ("06_ORNAMENT" 1 (
      (9551.9084 5142.0305) (9553.5267 5139.0382) (9557.9389 5136.5954) (9563.9542 5135.0229) (9569.9847 5134.1985)
      (9574.4885 5133.6336) (9576.5038 5132.6107) (9575.8015 5130.4733) (9573.0076 5126.8855) (9569.3282 5122.0458)
      (9566.1985 5116.687) (9564.7939 5111.8321) (9565.771 5108.5649) (9569.0382 5107.6031) (9573.8779 5108.9924)
      (9579.2519 5112.1221) (9584.0916 5115.8015) (9587.6794 5118.5954) (9589.8168 5119.2977) (9590.8397 5117.2977)
      (9591.4046 5112.7786) (9592.2137 5106.7634) (9593.8015 5100.7481) (9596.2443 5096.3206) (9599.2366 5094.7023)
      (9602.229 5096.3206) (9604.6718 5100.7481) (9606.2595 5106.7634) (9607.084 5112.7786) (9607.6336 5117.2977)
      (9608.6565 5119.2977) (9610.7939 5118.5954) (9614.3817 5115.8015) (9619.2214 5112.1221) (9624.5954 5108.9924)
      (9629.4351 5107.6031) (9632.7023 5108.5649) (9633.6794 5111.8321) (9632.2748 5116.687) (9629.145 5122.0458)
      (9625.4656 5126.8855) (9622.6718 5130.4733) (9621.9695 5132.6107) (9623.9847 5133.6336) (9628.4885 5134.1985)
      (9634.5191 5135.0229) (9640.5344 5136.5954) (9644.9466 5139.0382) (9646.5649 5142.0305) (9644.9466 5145.0382)
      (9640.5344 5147.4656) (9634.5191 5149.0534) (9628.4885 5149.8779) (9623.9847 5150.4427) (9621.9695 5151.4504)
      (9622.6718 5153.5878) (9625.4656 5157.1756) (9629.145 5162.0153) (9632.2748 5167.3893) (9633.6794 5172.2443)
      (9632.7023 5175.4962) (9629.4351 5176.4733) (9624.5954 5175.084) (9619.2214 5171.9389) (9614.3817 5168.2748)
      (9610.7939 5165.4809) (9608.6565 5164.7786) (9607.6336 5166.7786) (9607.084 5171.2977) (9606.2595 5177.313)
      (9604.6718 5183.3282) (9602.229 5187.7405) (9599.2366 5189.3588) (9596.2443 5187.7405) (9593.8015 5183.3282)
      (9592.2137 5177.313) (9591.4046 5171.2977) (9590.8397 5166.7786) (9589.8168 5164.7786) (9587.6794 5165.4809)
      (9584.0916 5168.2748) (9579.2519 5171.9389) (9573.8779 5175.084) (9569.0382 5176.4733) (9565.771 5175.4962)
      (9564.7939 5172.2443) (9566.1985 5167.3893) (9569.3282 5162.0153) (9573.0076 5157.1756) (9575.8015 5153.5878)
      (9576.5038 5151.4504) (9574.4885 5150.4427) (9569.9847 5149.8779) (9563.9542 5149.0534) (9557.9389 5147.4656)
      (9553.5267 5145.0382)
    ))
    ; P2700 -- see feature_dimensions_mm.csv
    ("06_ORNAMENT" 1 (
      (9551.9084 4851.9542) (9553.5267 4848.9618) (9557.9389 4846.5191) (9563.9542 4844.9466) (9569.9847 4844.1221)
      (9574.4885 4843.5573) (9576.5038 4842.5344) (9575.8015 4840.3969) (9573.0076 4836.8092) (9569.3282 4831.9695)
      (9566.1985 4826.6107) (9564.7939 4821.7557) (9565.771 4818.4885) (9569.0382 4817.5267) (9573.8779 4818.916)
      (9579.2519 4822.0458) (9584.0916 4825.7252) (9587.6794 4828.5191) (9589.8168 4829.2214) (9590.8397 4827.2214)
      (9591.4046 4822.7023) (9592.2137 4816.687) (9593.8015 4810.6718) (9596.2443 4806.2443) (9599.2366 4804.626)
      (9602.229 4806.2443) (9604.6718 4810.6718) (9606.2595 4816.687) (9607.084 4822.7023) (9607.6336 4827.2214)
      (9608.6565 4829.2214) (9610.7939 4828.5191) (9614.3817 4825.7252) (9619.2214 4822.0458) (9624.5954 4818.916)
      (9629.4351 4817.5267) (9632.7023 4818.4885) (9633.6794 4821.7557) (9632.2748 4826.6107) (9629.145 4831.9695)
      (9625.4656 4836.8092) (9622.6718 4840.3969) (9621.9695 4842.5344) (9623.9847 4843.5573) (9628.4885 4844.1221)
      (9634.5191 4844.9466) (9640.5344 4846.5191) (9644.9466 4848.9618) (9646.5649 4851.9542) (9644.9466 4854.9618)
      (9640.5344 4857.3893) (9634.5191 4858.9771) (9628.4885 4859.8015) (9623.9847 4860.3664) (9621.9695 4861.374)
      (9622.6718 4863.5115) (9625.4656 4867.0992) (9629.145 4871.9389) (9632.2748 4877.313) (9633.6794 4882.1679)
      (9632.7023 4885.4198) (9629.4351 4886.3969) (9624.5954 4885.0076) (9619.2214 4881.8626) (9614.3817 4878.1985)
      (9610.7939 4875.4046) (9608.6565 4874.7023) (9607.6336 4876.7023) (9607.084 4881.2214) (9606.2595 4887.2366)
      (9604.6718 4893.2519) (9602.229 4897.6641) (9599.2366 4899.2824) (9596.2443 4897.6641) (9593.8015 4893.2519)
      (9592.2137 4887.2366) (9591.4046 4881.2214) (9590.8397 4876.7023) (9589.8168 4874.7023) (9587.6794 4875.4046)
      (9584.0916 4878.1985) (9579.2519 4881.8626) (9573.8779 4885.0076) (9569.0382 4886.3969) (9565.771 4885.4198)
      (9564.7939 4882.1679) (9566.1985 4877.313) (9569.3282 4871.9389) (9573.0076 4867.0992) (9575.8015 4863.5115)
      (9576.5038 4861.374) (9574.4885 4860.3664) (9569.9847 4859.8015) (9563.9542 4858.9771) (9557.9389 4857.3893)
      (9553.5267 4854.9618)
    ))
    ; P2701 -- see feature_dimensions_mm.csv
    ("06_ORNAMENT" 1 (
      (9551.9084 4561.8779) (9553.5267 4558.8855) (9557.9389 4556.4427) (9563.9542 4554.8702) (9569.9847 4554.0458)
      (9574.4885 4553.4809) (9576.5038 4552.458) (9575.8015 4550.3206) (9573.0076 4546.7328) (9569.3282 4541.8931)
      (9566.1985 4536.5344) (9564.7939 4531.6794) (9565.771 4528.4122) (9569.0382 4527.4504) (9573.8779 4528.8397)
      (9579.2519 4531.9695) (9584.0916 4535.6489) (9587.6794 4538.4427) (9589.8168 4539.145) (9590.8397 4537.145)
      (9591.4046 4532.626) (9592.2137 4526.6107) (9593.8015 4520.5954) (9596.2443 4516.1679) (9599.2366 4514.5496)
      (9602.229 4516.1679) (9604.6718 4520.5954) (9606.2595 4526.6107) (9607.084 4532.626) (9607.6336 4537.145)
      (9608.6565 4539.145) (9610.7939 4538.4427) (9614.3817 4535.6489) (9619.2214 4531.9695) (9624.5954 4528.8397)
      (9629.4351 4527.4504) (9632.7023 4528.4122) (9633.6794 4531.6794) (9632.2748 4536.5344) (9629.145 4541.8931)
      (9625.4656 4546.7328) (9622.6718 4550.3206) (9621.9695 4552.458) (9623.9847 4553.4809) (9628.4885 4554.0458)
      (9634.5191 4554.8702) (9640.5344 4556.4427) (9644.9466 4558.8855) (9646.5649 4561.8779) (9644.9466 4564.8855)
      (9640.5344 4567.313) (9634.5191 4568.9008) (9628.4885 4569.7252) (9623.9847 4570.2901) (9621.9695 4571.2977)
      (9622.6718 4573.4351) (9625.4656 4577.0229) (9629.145 4581.8626) (9632.2748 4587.2366) (9633.6794 4592.0916)
      (9632.7023 4595.3435) (9629.4351 4596.3206) (9624.5954 4594.9313) (9619.2214 4591.7863) (9614.3817 4588.1221)
      (9610.7939 4585.3282) (9608.6565 4584.626) (9607.6336 4586.626) (9607.084 4591.145) (9606.2595 4597.1603)
      (9604.6718 4603.1756) (9602.229 4607.5878) (9599.2366 4609.2061) (9596.2443 4607.5878) (9593.8015 4603.1756)
      (9592.2137 4597.1603) (9591.4046 4591.145) (9590.8397 4586.626) (9589.8168 4584.626) (9587.6794 4585.3282)
      (9584.0916 4588.1221) (9579.2519 4591.7863) (9573.8779 4594.9313) (9569.0382 4596.3206) (9565.771 4595.3435)
      (9564.7939 4592.0916) (9566.1985 4587.2366) (9569.3282 4581.8626) (9573.0076 4577.0229) (9575.8015 4573.4351)
      (9576.5038 4571.2977) (9574.4885 4570.2901) (9569.9847 4569.7252) (9563.9542 4568.9008) (9557.9389 4567.313)
      (9553.5267 4564.8855)
    ))
    ; P2702 -- see feature_dimensions_mm.csv
    ("06_ORNAMENT" 1 (
      (9551.9084 4271.8015) (9553.5267 4268.8092) (9557.9389 4266.3664) (9563.9542 4264.7939) (9569.9847 4263.9695)
      (9574.4885 4263.4046) (9576.5038 4262.3817) (9575.8015 4260.2443) (9573.0076 4256.6565) (9569.3282 4251.8168)
      (9566.1985 4246.458) (9564.7939 4241.6031) (9565.771 4238.3359) (9569.0382 4237.374) (9573.8779 4238.7634)
      (9579.2519 4241.8931) (9584.0916 4245.5725) (9587.6794 4248.3664) (9589.8168 4249.0687) (9590.8397 4247.0687)
      (9591.4046 4242.5496) (9592.2137 4236.5344) (9593.8015 4230.5191) (9596.2443 4226.0916) (9599.2366 4224.4733)
      (9602.229 4226.0916) (9604.6718 4230.5191) (9606.2595 4236.5344) (9607.084 4242.5496) (9607.6336 4247.0687)
      (9608.6565 4249.0687) (9610.7939 4248.3664) (9614.3817 4245.5725) (9619.2214 4241.8931) (9624.5954 4238.7634)
      (9629.4351 4237.374) (9632.7023 4238.3359) (9633.6794 4241.6031) (9632.2748 4246.458) (9629.145 4251.8168)
      (9625.4656 4256.6565) (9622.6718 4260.2443) (9621.9695 4262.3817) (9623.9847 4263.4046) (9628.4885 4263.9695)
      (9634.5191 4264.7939) (9640.5344 4266.3664) (9644.9466 4268.8092) (9646.5649 4271.8015) (9644.9466 4274.8092)
      (9640.5344 4277.2366) (9634.5191 4278.8244) (9628.4885 4279.6489) (9623.9847 4280.2137) (9621.9695 4281.2214)
      (9622.6718 4283.3588) (9625.4656 4286.9466) (9629.145 4291.7863) (9632.2748 4297.1603) (9633.6794 4302.0153)
      (9632.7023 4305.2672) (9629.4351 4306.2443) (9624.5954 4304.855) (9619.2214 4301.7099) (9614.3817 4298.0458)
      (9610.7939 4295.2519) (9608.6565 4294.5496) (9607.6336 4296.5496) (9607.084 4301.0687) (9606.2595 4307.084)
      (9604.6718 4313.0992) (9602.229 4317.5115) (9599.2366 4319.1298) (9596.2443 4317.5115) (9593.8015 4313.0992)
      (9592.2137 4307.084) (9591.4046 4301.0687) (9590.8397 4296.5496) (9589.8168 4294.5496) (9587.6794 4295.2519)
      (9584.0916 4298.0458) (9579.2519 4301.7099) (9573.8779 4304.855) (9569.0382 4306.2443) (9565.771 4305.2672)
      (9564.7939 4302.0153) (9566.1985 4297.1603) (9569.3282 4291.7863) (9573.0076 4286.9466) (9575.8015 4283.3588)
      (9576.5038 4281.2214) (9574.4885 4280.2137) (9569.9847 4279.6489) (9563.9542 4278.8244) (9557.9389 4277.2366)
      (9553.5267 4274.8092)
    ))
    ; P2703 -- see feature_dimensions_mm.csv
    ("06_ORNAMENT" 1 (
      (9551.9084 3981.7252) (9553.5267 3978.7328) (9557.9389 3976.2901) (9563.9542 3974.7176) (9569.9847 3973.8931)
      (9574.4885 3973.3282) (9576.5038 3972.3053) (9575.8015 3970.1679) (9573.0076 3966.5802) (9569.3282 3961.7405)
      (9566.1985 3956.3817) (9564.7939 3951.5267) (9565.771 3948.2595) (9569.0382 3947.2977) (9573.8779 3948.687)
      (9579.2519 3951.8168) (9584.0916 3955.4962) (9587.6794 3958.2901) (9589.8168 3958.9924) (9590.8397 3956.9924)
      (9591.4046 3952.4733) (9592.2137 3946.458) (9593.8015 3940.4427) (9596.2443 3936.0153) (9599.2366 3934.3969)
      (9602.229 3936.0153) (9604.6718 3940.4427) (9606.2595 3946.458) (9607.084 3952.4733) (9607.6336 3956.9924)
      (9608.6565 3958.9924) (9610.7939 3958.2901) (9614.3817 3955.4962) (9619.2214 3951.8168) (9624.5954 3948.687)
      (9629.4351 3947.2977) (9632.7023 3948.2595) (9633.6794 3951.5267) (9632.2748 3956.3817) (9629.145 3961.7405)
      (9625.4656 3966.5802) (9622.6718 3970.1679) (9621.9695 3972.3053) (9623.9847 3973.3282) (9628.4885 3973.8931)
      (9634.5191 3974.7176) (9640.5344 3976.2901) (9644.9466 3978.7328) (9646.5649 3981.7252) (9644.9466 3984.7328)
      (9640.5344 3987.1603) (9634.5191 3988.7481) (9628.4885 3989.5725) (9623.9847 3990.1374) (9621.9695 3991.145)
      (9622.6718 3993.2824) (9625.4656 3996.8702) (9629.145 4001.7099) (9632.2748 4007.084) (9633.6794 4011.9389)
      (9632.7023 4015.1908) (9629.4351 4016.1679) (9624.5954 4014.7786) (9619.2214 4011.6336) (9614.3817 4007.9695)
      (9610.7939 4005.1756) (9608.6565 4004.4733) (9607.6336 4006.4733) (9607.084 4010.9924) (9606.2595 4017.0076)
      (9604.6718 4023.0229) (9602.229 4027.4351) (9599.2366 4029.0534) (9596.2443 4027.4351) (9593.8015 4023.0229)
      (9592.2137 4017.0076) (9591.4046 4010.9924) (9590.8397 4006.4733) (9589.8168 4004.4733) (9587.6794 4005.1756)
      (9584.0916 4007.9695) (9579.2519 4011.6336) (9573.8779 4014.7786) (9569.0382 4016.1679) (9565.771 4015.1908)
      (9564.7939 4011.9389) (9566.1985 4007.084) (9569.3282 4001.7099) (9573.0076 3996.8702) (9575.8015 3993.2824)
      (9576.5038 3991.145) (9574.4885 3990.1374) (9569.9847 3989.5725) (9563.9542 3988.7481) (9557.9389 3987.1603)
      (9553.5267 3984.7328)
    ))
    ; P2704 -- see feature_dimensions_mm.csv
    ("06_ORNAMENT" 1 (
      (9580.916 5214.5496) (9599.2366 5193.9389) (9617.5573 5214.5496) (9599.2366 5235.1603)
    ))
    ; P2705 -- see feature_dimensions_mm.csv
    ("06_ORNAMENT" 1 (
      (9580.916 4924.4733) (9599.2366 4903.8626) (9617.5573 4924.4733) (9599.2366 4945.084)
    ))
    ; P2706 -- see feature_dimensions_mm.csv
    ("06_ORNAMENT" 1 (
      (9580.916 4634.3969) (9599.2366 4613.7863) (9617.5573 4634.3969) (9599.2366 4655.0076)
    ))
    ; P2707 -- see feature_dimensions_mm.csv
    ("06_ORNAMENT" 1 (
      (9580.916 4344.3206) (9599.2366 4323.7099) (9617.5573 4344.3206) (9599.2366 4364.9313)
    ))
    ; P2708 -- see feature_dimensions_mm.csv
    ("06_ORNAMENT" 1 (
      (9580.916 4054.2443) (9599.2366 4033.6336) (9617.5573 4054.2443) (9599.2366 4074.855)
    ))
    ; P2709 -- see feature_dimensions_mm.csv
    ("06_ORNAMENT" 1 (
      (9587.3282 5432.1069) (9588.229 5427.5573) (9590.8092 5423.6947) (9594.687 5421.1145) (9599.2366 5420.1985)
      (9603.7863 5421.1145) (9607.6641 5423.6947) (9610.2443 5427.5573) (9611.145 5432.1069) (9610.2443 5436.6718)
      (9607.6641 5440.5344) (9603.7863 5443.1145) (9599.2366 5444.0153) (9594.687 5443.1145) (9590.8092 5440.5344)
      (9588.229 5436.6718)
    ))
    ; P2710 -- see feature_dimensions_mm.csv
    ("06_ORNAMENT" 1 (
      (9587.3282 5142.0305) (9588.229 5137.4809) (9590.8092 5133.6183) (9594.687 5131.0382) (9599.2366 5130.1221)
      (9603.7863 5131.0382) (9607.6641 5133.6183) (9610.2443 5137.4809) (9611.145 5142.0305) (9610.2443 5146.5954)
      (9607.6641 5150.458) (9603.7863 5153.0382) (9599.2366 5153.9389) (9594.687 5153.0382) (9590.8092 5150.458)
      (9588.229 5146.5954)
    ))
    ; P2711 -- see feature_dimensions_mm.csv
    ("06_ORNAMENT" 1 (
      (9587.3282 4851.9542) (9588.229 4847.4046) (9590.8092 4843.542) (9594.687 4840.9618) (9599.2366 4840.0458)
      (9603.7863 4840.9618) (9607.6641 4843.542) (9610.2443 4847.4046) (9611.145 4851.9542) (9610.2443 4856.5191)
      (9607.6641 4860.3817) (9603.7863 4862.9618) (9599.2366 4863.8626) (9594.687 4862.9618) (9590.8092 4860.3817)
      (9588.229 4856.5191)
    ))
    ; P2712 -- see feature_dimensions_mm.csv
    ("06_ORNAMENT" 1 (
      (9587.3282 4561.8779) (9588.229 4557.3282) (9590.8092 4553.4656) (9594.687 4550.8855) (9599.2366 4549.9695)
      (9603.7863 4550.8855) (9607.6641 4553.4656) (9610.2443 4557.3282) (9611.145 4561.8779) (9610.2443 4566.4427)
      (9607.6641 4570.3053) (9603.7863 4572.8855) (9599.2366 4573.7863) (9594.687 4572.8855) (9590.8092 4570.3053)
      (9588.229 4566.4427)
    ))
    ; P2713 -- see feature_dimensions_mm.csv
    ("06_ORNAMENT" 1 (
      (9587.3282 4271.8015) (9588.229 4267.2519) (9590.8092 4263.3893) (9594.687 4260.8092) (9599.2366 4259.8931)
      (9603.7863 4260.8092) (9607.6641 4263.3893) (9610.2443 4267.2519) (9611.145 4271.8015) (9610.2443 4276.3664)
      (9607.6641 4280.229) (9603.7863 4282.8092) (9599.2366 4283.7099) (9594.687 4282.8092) (9590.8092 4280.229)
      (9588.229 4276.3664)
    ))
    ; P2714 -- see feature_dimensions_mm.csv
    ("06_ORNAMENT" 1 (
      (9587.3282 3981.7252) (9588.229 3977.1756) (9590.8092 3973.313) (9594.687 3970.7328) (9599.2366 3969.8168)
      (9603.7863 3970.7328) (9607.6641 3973.313) (9610.2443 3977.1756) (9611.145 3981.7252) (9610.2443 3986.2901)
      (9607.6641 3990.1527) (9603.7863 3992.7328) (9599.2366 3993.6336) (9594.687 3992.7328) (9590.8092 3990.1527)
      (9588.229 3986.2901)
    ))
    ; P2715 -- see feature_dimensions_mm.csv
    ("06_ORNAMENT" 1 (
      (9624.4275 5287.0687) (9626.0458 5284.0763) (9630.458 5281.6336) (9636.4733 5280.0611) (9642.5038 5279.2366)
      (9647.0076 5278.6718) (9649.0229 5277.6489) (9648.3206 5275.5115) (9645.5267 5271.9237) (9641.8473 5267.084)
      (9638.7176 5261.7252) (9637.313 5256.8702) (9638.2901 5253.6031) (9641.5573 5252.6412) (9646.3969 5254.0305)
      (9651.771 5257.1603) (9656.6107 5260.8397) (9660.1985 5263.6336) (9662.3359 5264.3359) (9663.3588 5262.3359)
      (9663.9237 5257.8168) (9664.7328 5251.8015) (9666.3206 5245.7863) (9668.7634 5241.3588) (9671.7557 5239.7405)
      (9674.7481 5241.3588) (9677.1908 5245.7863) (9678.7786 5251.8015) (9679.6031 5257.8168) (9680.1527 5262.3359)
      (9681.1756 5264.3359) (9683.313 5263.6336) (9686.9008 5260.8397) (9691.7405 5257.1603) (9697.1145 5254.0305)
      (9701.9542 5252.6412) (9705.2214 5253.6031) (9706.1985 5256.8702) (9704.7939 5261.7252) (9701.6641 5267.084)
      (9697.9847 5271.9237) (9695.1908 5275.5115) (9694.4885 5277.6489) (9696.5038 5278.6718) (9701.0076 5279.2366)
      (9707.0382 5280.0611) (9713.0534 5281.6336) (9717.4656 5284.0763) (9719.084 5287.0687) (9717.4656 5290.0763)
      (9713.0534 5292.5038) (9707.0382 5294.0916) (9701.0076 5294.916) (9696.5038 5295.4809) (9694.4885 5296.4885)
      (9695.1908 5298.626) (9697.9847 5302.2137) (9701.6641 5307.0534) (9704.7939 5312.4275) (9706.1985 5317.2824)
      (9705.2214 5320.5344) (9701.9542 5321.5115) (9697.1145 5320.1221) (9691.7405 5316.9771) (9686.9008 5313.313)
      (9683.313 5310.5191) (9681.1756 5309.8168) (9680.1527 5311.8168) (9679.6031 5316.3359) (9678.7786 5322.3511)
      (9677.1908 5328.3664) (9674.7481 5332.7786) (9671.7557 5334.3969) (9668.7634 5332.7786) (9666.3206 5328.3664)
      (9664.7328 5322.3511) (9663.9237 5316.3359) (9663.3588 5311.8168) (9662.3359 5309.8168) (9660.1985 5310.5191)
      (9656.6107 5313.313) (9651.771 5316.9771) (9646.3969 5320.1221) (9641.5573 5321.5115) (9638.2901 5320.5344)
      (9637.313 5317.2824) (9638.7176 5312.4275) (9641.8473 5307.0534) (9645.5267 5302.2137) (9648.3206 5298.626)
      (9649.0229 5296.4885) (9647.0076 5295.4809) (9642.5038 5294.916) (9636.4733 5294.0916) (9630.458 5292.5038)
      (9626.0458 5290.0763)
    ))
    ; P2716 -- see feature_dimensions_mm.csv
    ("06_ORNAMENT" 1 (
      (9624.4275 4996.9924) (9626.0458 4994.0) (9630.458 4991.5573) (9636.4733 4989.9847) (9642.5038 4989.1603)
      (9647.0076 4988.5954) (9649.0229 4987.5725) (9648.3206 4985.4351) (9645.5267 4981.8473) (9641.8473 4977.0076)
      (9638.7176 4971.6489) (9637.313 4966.7939) (9638.2901 4963.5267) (9641.5573 4962.5649) (9646.3969 4963.9542)
      (9651.771 4967.084) (9656.6107 4970.7634) (9660.1985 4973.5573) (9662.3359 4974.2595) (9663.3588 4972.2595)
      (9663.9237 4967.7405) (9664.7328 4961.7252) (9666.3206 4955.7099) (9668.7634 4951.2824) (9671.7557 4949.6641)
      (9674.7481 4951.2824) (9677.1908 4955.7099) (9678.7786 4961.7252) (9679.6031 4967.7405) (9680.1527 4972.2595)
      (9681.1756 4974.2595) (9683.313 4973.5573) (9686.9008 4970.7634) (9691.7405 4967.084) (9697.1145 4963.9542)
      (9701.9542 4962.5649) (9705.2214 4963.5267) (9706.1985 4966.7939) (9704.7939 4971.6489) (9701.6641 4977.0076)
      (9697.9847 4981.8473) (9695.1908 4985.4351) (9694.4885 4987.5725) (9696.5038 4988.5954) (9701.0076 4989.1603)
      (9707.0382 4989.9847) (9713.0534 4991.5573) (9717.4656 4994.0) (9719.084 4996.9924) (9717.4656 5000.0)
      (9713.0534 5002.4275) (9707.0382 5004.0153) (9701.0076 5004.8397) (9696.5038 5005.4046) (9694.4885 5006.4122)
      (9695.1908 5008.5496) (9697.9847 5012.1374) (9701.6641 5016.9771) (9704.7939 5022.3511) (9706.1985 5027.2061)
      (9705.2214 5030.458) (9701.9542 5031.4351) (9697.1145 5030.0458) (9691.7405 5026.9008) (9686.9008 5023.2366)
      (9683.313 5020.4427) (9681.1756 5019.7405) (9680.1527 5021.7405) (9679.6031 5026.2595) (9678.7786 5032.2748)
      (9677.1908 5038.2901) (9674.7481 5042.7023) (9671.7557 5044.3206) (9668.7634 5042.7023) (9666.3206 5038.2901)
      (9664.7328 5032.2748) (9663.9237 5026.2595) (9663.3588 5021.7405) (9662.3359 5019.7405) (9660.1985 5020.4427)
      (9656.6107 5023.2366) (9651.771 5026.9008) (9646.3969 5030.0458) (9641.5573 5031.4351) (9638.2901 5030.458)
      (9637.313 5027.2061) (9638.7176 5022.3511) (9641.8473 5016.9771) (9645.5267 5012.1374) (9648.3206 5008.5496)
      (9649.0229 5006.4122) (9647.0076 5005.4046) (9642.5038 5004.8397) (9636.4733 5004.0153) (9630.458 5002.4275)
      (9626.0458 5000.0)
    ))
    ; P2717 -- see feature_dimensions_mm.csv
    ("06_ORNAMENT" 1 (
      (9624.4275 4706.916) (9626.0458 4703.9237) (9630.458 4701.4809) (9636.4733 4699.9084) (9642.5038 4699.084)
      (9647.0076 4698.5191) (9649.0229 4697.4962) (9648.3206 4695.3588) (9645.5267 4691.771) (9641.8473 4686.9313)
      (9638.7176 4681.5725) (9637.313 4676.7176) (9638.2901 4673.4504) (9641.5573 4672.4885) (9646.3969 4673.8779)
      (9651.771 4677.0076) (9656.6107 4680.687) (9660.1985 4683.4809) (9662.3359 4684.1832) (9663.3588 4682.1832)
      (9663.9237 4677.6641) (9664.7328 4671.6489) (9666.3206 4665.6336) (9668.7634 4661.2061) (9671.7557 4659.5878)
      (9674.7481 4661.2061) (9677.1908 4665.6336) (9678.7786 4671.6489) (9679.6031 4677.6641) (9680.1527 4682.1832)
      (9681.1756 4684.1832) (9683.313 4683.4809) (9686.9008 4680.687) (9691.7405 4677.0076) (9697.1145 4673.8779)
      (9701.9542 4672.4885) (9705.2214 4673.4504) (9706.1985 4676.7176) (9704.7939 4681.5725) (9701.6641 4686.9313)
      (9697.9847 4691.771) (9695.1908 4695.3588) (9694.4885 4697.4962) (9696.5038 4698.5191) (9701.0076 4699.084)
      (9707.0382 4699.9084) (9713.0534 4701.4809) (9717.4656 4703.9237) (9719.084 4706.916) (9717.4656 4709.9237)
      (9713.0534 4712.3511) (9707.0382 4713.9389) (9701.0076 4714.7634) (9696.5038 4715.3282) (9694.4885 4716.3359)
      (9695.1908 4718.4733) (9697.9847 4722.0611) (9701.6641 4726.9008) (9704.7939 4732.2748) (9706.1985 4737.1298)
      (9705.2214 4740.3817) (9701.9542 4741.3588) (9697.1145 4739.9695) (9691.7405 4736.8244) (9686.9008 4733.1603)
      (9683.313 4730.3664) (9681.1756 4729.6641) (9680.1527 4731.6641) (9679.6031 4736.1832) (9678.7786 4742.1985)
      (9677.1908 4748.2137) (9674.7481 4752.626) (9671.7557 4754.2443) (9668.7634 4752.626) (9666.3206 4748.2137)
      (9664.7328 4742.1985) (9663.9237 4736.1832) (9663.3588 4731.6641) (9662.3359 4729.6641) (9660.1985 4730.3664)
      (9656.6107 4733.1603) (9651.771 4736.8244) (9646.3969 4739.9695) (9641.5573 4741.3588) (9638.2901 4740.3817)
      (9637.313 4737.1298) (9638.7176 4732.2748) (9641.8473 4726.9008) (9645.5267 4722.0611) (9648.3206 4718.4733)
      (9649.0229 4716.3359) (9647.0076 4715.3282) (9642.5038 4714.7634) (9636.4733 4713.9389) (9630.458 4712.3511)
      (9626.0458 4709.9237)
    ))
    ; P2718 -- see feature_dimensions_mm.csv
    ("06_ORNAMENT" 1 (
      (9624.4275 4126.7634) (9626.0458 4123.771) (9630.458 4121.3282) (9636.4733 4119.7557) (9642.5038 4118.9313)
      (9647.0076 4118.3664) (9649.0229 4117.3435) (9648.3206 4115.2061) (9645.5267 4111.6183) (9641.8473 4106.7786)
      (9638.7176 4101.4198) (9637.313 4096.5649) (9638.2901 4093.2977) (9641.5573 4092.3359) (9646.3969 4093.7252)
      (9651.771 4096.855) (9656.6107 4100.5344) (9660.1985 4103.3282) (9662.3359 4104.0305) (9663.3588 4102.0305)
      (9663.9237 4097.5115) (9664.7328 4091.4962) (9666.3206 4085.4809) (9668.7634 4081.0534) (9671.7557 4079.4351)
      (9674.7481 4081.0534) (9677.1908 4085.4809) (9678.7786 4091.4962) (9679.6031 4097.5115) (9680.1527 4102.0305)
      (9681.1756 4104.0305) (9683.313 4103.3282) (9686.9008 4100.5344) (9691.7405 4096.855) (9697.1145 4093.7252)
      (9701.9542 4092.3359) (9705.2214 4093.2977) (9706.1985 4096.5649) (9704.7939 4101.4198) (9701.6641 4106.7786)
      (9697.9847 4111.6183) (9695.1908 4115.2061) (9694.4885 4117.3435) (9696.5038 4118.3664) (9701.0076 4118.9313)
      (9707.0382 4119.7557) (9713.0534 4121.3282) (9717.4656 4123.771) (9719.084 4126.7634) (9717.4656 4129.771)
      (9713.0534 4132.1985) (9707.0382 4133.7863) (9701.0076 4134.6107) (9696.5038 4135.1756) (9694.4885 4136.1832)
      (9695.1908 4138.3206) (9697.9847 4141.9084) (9701.6641 4146.7481) (9704.7939 4152.1221) (9706.1985 4156.9771)
      (9705.2214 4160.229) (9701.9542 4161.2061) (9697.1145 4159.8168) (9691.7405 4156.6718) (9686.9008 4153.0076)
      (9683.313 4150.2137) (9681.1756 4149.5115) (9680.1527 4151.5115) (9679.6031 4156.0305) (9678.7786 4162.0458)
      (9677.1908 4168.0611) (9674.7481 4172.4733) (9671.7557 4174.0916) (9668.7634 4172.4733) (9666.3206 4168.0611)
      (9664.7328 4162.0458) (9663.9237 4156.0305) (9663.3588 4151.5115) (9662.3359 4149.5115) (9660.1985 4150.2137)
      (9656.6107 4153.0076) (9651.771 4156.6718) (9646.3969 4159.8168) (9641.5573 4161.2061) (9638.2901 4160.229)
      (9637.313 4156.9771) (9638.7176 4152.1221) (9641.8473 4146.7481) (9645.5267 4141.9084) (9648.3206 4138.3206)
      (9649.0229 4136.1832) (9647.0076 4135.1756) (9642.5038 4134.6107) (9636.4733 4133.7863) (9630.458 4132.1985)
      (9626.0458 4129.771)
    ))
    ; P2719 -- see feature_dimensions_mm.csv
    ("06_ORNAMENT" 1 (
      (9653.4351 5359.5878) (9671.7557 5338.9771) (9690.0763 5359.5878) (9671.7557 5380.1985)
    ))
    ; P2720 -- see feature_dimensions_mm.csv
    ("06_ORNAMENT" 1 (
      (9653.4351 5069.5115) (9671.7557 5048.9008) (9690.0763 5069.5115) (9671.7557 5090.1221)
    ))
    ; P2721 -- see feature_dimensions_mm.csv
    ("06_ORNAMENT" 1 (
      (9653.4351 4779.4351) (9671.7557 4758.8244) (9690.0763 4779.4351) (9671.7557 4800.0458)
    ))
    ; P2722 -- see feature_dimensions_mm.csv
    ("06_ORNAMENT" 1 (
      (9653.4351 4199.2824) (9671.7557 4178.6718) (9690.0763 4199.2824) (9671.7557 4219.8931)
    ))
    ; P2723 -- see feature_dimensions_mm.csv
    ("06_ORNAMENT" 1 (
      (9653.4351 3909.2061) (9671.7557 3888.5954) (9690.0763 3909.2061) (9671.7557 3929.8168)
    ))
    ; P2724 -- see feature_dimensions_mm.csv
    ("06_ORNAMENT" 1 (
      (9659.8473 5287.0687) (9660.7481 5282.5191) (9663.3282 5278.6565) (9667.2061 5276.0763) (9671.7557 5275.1603)
      (9676.3053 5276.0763) (9680.1832 5278.6565) (9682.7634 5282.5191) (9683.6641 5287.0687) (9682.7634 5291.6336)
      (9680.1832 5295.4962) (9676.3053 5298.0763) (9671.7557 5298.9771) (9667.2061 5298.0763) (9663.3282 5295.4962)
      (9660.7481 5291.6336)
    ))
    ; P2725 -- see feature_dimensions_mm.csv
    ("06_ORNAMENT" 1 (
      (9659.8473 4996.9924) (9660.7481 4992.4427) (9663.3282 4988.5802) (9667.2061 4986.0) (9671.7557 4985.084)
      (9676.3053 4986.0) (9680.1832 4988.5802) (9682.7634 4992.4427) (9683.6641 4996.9924) (9682.7634 5001.5573)
      (9680.1832 5005.4198) (9676.3053 5008.0) (9671.7557 5008.9008) (9667.2061 5008.0) (9663.3282 5005.4198)
      (9660.7481 5001.5573)
    ))
    ; P2726 -- see feature_dimensions_mm.csv
    ("06_ORNAMENT" 1 (
      (9659.8473 4706.916) (9660.7481 4702.3664) (9663.3282 4698.5038) (9667.2061 4695.9237) (9671.7557 4695.0076)
      (9676.3053 4695.9237) (9680.1832 4698.5038) (9682.7634 4702.3664) (9683.6641 4706.916) (9682.7634 4711.4809)
      (9680.1832 4715.3435) (9676.3053 4717.9237) (9671.7557 4718.8244) (9667.2061 4717.9237) (9663.3282 4715.3435)
      (9660.7481 4711.4809)
    ))
    ; P2727 -- see feature_dimensions_mm.csv
    ("06_ORNAMENT" 1 (
      (9659.8473 4126.7634) (9660.7481 4122.2137) (9663.3282 4118.3511) (9667.2061 4115.771) (9671.7557 4114.855)
      (9676.3053 4115.771) (9680.1832 4118.3511) (9682.7634 4122.2137) (9683.6641 4126.7634) (9682.7634 4131.3282)
      (9680.1832 4135.1908) (9676.3053 4137.771) (9671.7557 4138.6718) (9667.2061 4137.771) (9663.3282 4135.1908)
      (9660.7481 4131.3282)
    ))
    ; P2728 -- see feature_dimensions_mm.csv
    ("06_ORNAMENT" 1 (
      (9696.9466 5142.0305) (9698.5649 5139.0382) (9702.9771 5136.5954) (9708.9924 5135.0229) (9715.0229 5134.1985)
      (9719.5267 5133.6336) (9721.542 5132.6107) (9720.8397 5130.4733) (9718.0458 5126.8855) (9714.3664 5122.0458)
      (9711.2366 5116.687) (9709.8321 5111.8321) (9710.8092 5108.5649) (9714.0763 5107.6031) (9718.916 5108.9924)
      (9724.2901 5112.1221) (9729.1298 5115.8015) (9732.7176 5118.5954) (9734.855 5119.2977) (9735.8779 5117.2977)
      (9736.4427 5112.7786) (9737.2519 5106.7634) (9738.8397 5100.7481) (9741.2824 5096.3206) (9744.2748 5094.7023)
      (9747.2672 5096.3206) (9749.7099 5100.7481) (9751.2977 5106.7634) (9752.1221 5112.7786) (9752.6718 5117.2977)
      (9753.6947 5119.2977) (9755.8321 5118.5954) (9759.4198 5115.8015) (9764.2595 5112.1221) (9769.6336 5108.9924)
      (9774.4733 5107.6031) (9777.7405 5108.5649) (9778.7176 5111.8321) (9777.313 5116.687) (9774.1832 5122.0458)
      (9770.5038 5126.8855) (9767.7099 5130.4733) (9767.0076 5132.6107) (9769.0229 5133.6336) (9773.5267 5134.1985)
      (9779.5573 5135.0229) (9785.5725 5136.5954) (9789.9847 5139.0382) (9791.6031 5142.0305) (9789.9847 5145.0382)
      (9785.5725 5147.4656) (9779.5573 5149.0534) (9773.5267 5149.8779) (9769.0229 5150.4427) (9767.0076 5151.4504)
      (9767.7099 5153.5878) (9770.5038 5157.1756) (9774.1832 5162.0153) (9777.313 5167.3893) (9778.7176 5172.2443)
      (9777.7405 5175.4962) (9774.4733 5176.4733) (9769.6336 5175.084) (9764.2595 5171.9389) (9759.4198 5168.2748)
      (9755.8321 5165.4809) (9753.6947 5164.7786) (9752.6718 5166.7786) (9752.1221 5171.2977) (9751.2977 5177.313)
      (9749.7099 5183.3282) (9747.2672 5187.7405) (9744.2748 5189.3588) (9741.2824 5187.7405) (9738.8397 5183.3282)
      (9737.2519 5177.313) (9736.4427 5171.2977) (9735.8779 5166.7786) (9734.855 5164.7786) (9732.7176 5165.4809)
      (9729.1298 5168.2748) (9724.2901 5171.9389) (9718.916 5175.084) (9714.0763 5176.4733) (9710.8092 5175.4962)
      (9709.8321 5172.2443) (9711.2366 5167.3893) (9714.3664 5162.0153) (9718.0458 5157.1756) (9720.8397 5153.5878)
      (9721.542 5151.4504) (9719.5267 5150.4427) (9715.0229 5149.8779) (9708.9924 5149.0534) (9702.9771 5147.4656)
      (9698.5649 5145.0382)
    ))
    ; P2729 -- see feature_dimensions_mm.csv
    ("06_ORNAMENT" 1 (
      (9696.9466 4851.9542) (9698.5649 4848.9618) (9702.9771 4846.5191) (9708.9924 4844.9466) (9715.0229 4844.1221)
      (9719.5267 4843.5573) (9721.542 4842.5344) (9720.8397 4840.3969) (9718.0458 4836.8092) (9714.3664 4831.9695)
      (9711.2366 4826.6107) (9709.8321 4821.7557) (9710.8092 4818.4885) (9714.0763 4817.5267) (9718.916 4818.916)
      (9724.2901 4822.0458) (9729.1298 4825.7252) (9732.7176 4828.5191) (9734.855 4829.2214) (9735.8779 4827.2214)
      (9736.4427 4822.7023) (9737.2519 4816.687) (9738.8397 4810.6718) (9741.2824 4806.2443) (9744.2748 4804.626)
      (9747.2672 4806.2443) (9749.7099 4810.6718) (9751.2977 4816.687) (9752.1221 4822.7023) (9752.6718 4827.2214)
      (9753.6947 4829.2214) (9755.8321 4828.5191) (9759.4198 4825.7252) (9764.2595 4822.0458) (9769.6336 4818.916)
      (9774.4733 4817.5267) (9777.7405 4818.4885) (9778.7176 4821.7557) (9777.313 4826.6107) (9774.1832 4831.9695)
      (9770.5038 4836.8092) (9767.7099 4840.3969) (9767.0076 4842.5344) (9769.0229 4843.5573) (9773.5267 4844.1221)
      (9779.5573 4844.9466) (9785.5725 4846.5191) (9789.9847 4848.9618) (9791.6031 4851.9542) (9789.9847 4854.9618)
      (9785.5725 4857.3893) (9779.5573 4858.9771) (9773.5267 4859.8015) (9769.0229 4860.3664) (9767.0076 4861.374)
      (9767.7099 4863.5115) (9770.5038 4867.0992) (9774.1832 4871.9389) (9777.313 4877.313) (9778.7176 4882.1679)
      (9777.7405 4885.4198) (9774.4733 4886.3969) (9769.6336 4885.0076) (9764.2595 4881.8626) (9759.4198 4878.1985)
      (9755.8321 4875.4046) (9753.6947 4874.7023) (9752.6718 4876.7023) (9752.1221 4881.2214) (9751.2977 4887.2366)
      (9749.7099 4893.2519) (9747.2672 4897.6641) (9744.2748 4899.2824) (9741.2824 4897.6641) (9738.8397 4893.2519)
      (9737.2519 4887.2366) (9736.4427 4881.2214) (9735.8779 4876.7023) (9734.855 4874.7023) (9732.7176 4875.4046)
      (9729.1298 4878.1985) (9724.2901 4881.8626) (9718.916 4885.0076) (9714.0763 4886.3969) (9710.8092 4885.4198)
      (9709.8321 4882.1679) (9711.2366 4877.313) (9714.3664 4871.9389) (9718.0458 4867.0992) (9720.8397 4863.5115)
      (9721.542 4861.374) (9719.5267 4860.3664) (9715.0229 4859.8015) (9708.9924 4858.9771) (9702.9771 4857.3893)
      (9698.5649 4854.9618)
    ))
    ; P2730 -- see feature_dimensions_mm.csv
    ("06_ORNAMENT" 1 (
      (9696.9466 4561.8779) (9698.5649 4558.8855) (9702.9771 4556.4427) (9708.9924 4554.8702) (9715.0229 4554.0458)
      (9719.5267 4553.4809) (9721.542 4552.458) (9720.8397 4550.3206) (9718.0458 4546.7328) (9714.3664 4541.8931)
      (9711.2366 4536.5344) (9709.8321 4531.6794) (9710.8092 4528.4122) (9714.0763 4527.4504) (9718.916 4528.8397)
      (9724.2901 4531.9695) (9729.1298 4535.6489) (9732.7176 4538.4427) (9734.855 4539.145) (9735.8779 4537.145)
      (9736.4427 4532.626) (9737.2519 4526.6107) (9738.8397 4520.5954) (9741.2824 4516.1679) (9744.2748 4514.5496)
      (9747.2672 4516.1679) (9749.7099 4520.5954) (9751.2977 4526.6107) (9752.1221 4532.626) (9752.6718 4537.145)
      (9753.6947 4539.145) (9755.8321 4538.4427) (9759.4198 4535.6489) (9764.2595 4531.9695) (9769.6336 4528.8397)
      (9774.4733 4527.4504) (9777.7405 4528.4122) (9778.7176 4531.6794) (9777.313 4536.5344) (9774.1832 4541.8931)
      (9770.5038 4546.7328) (9767.7099 4550.3206) (9767.0076 4552.458) (9769.0229 4553.4809) (9773.5267 4554.0458)
      (9779.5573 4554.8702) (9785.5725 4556.4427) (9789.9847 4558.8855) (9791.6031 4561.8779) (9789.9847 4564.8855)
      (9785.5725 4567.313) (9779.5573 4568.9008) (9773.5267 4569.7252) (9769.0229 4570.2901) (9767.0076 4571.2977)
      (9767.7099 4573.4351) (9770.5038 4577.0229) (9774.1832 4581.8626) (9777.313 4587.2366) (9778.7176 4592.0916)
      (9777.7405 4595.3435) (9774.4733 4596.3206) (9769.6336 4594.9313) (9764.2595 4591.7863) (9759.4198 4588.1221)
      (9755.8321 4585.3282) (9753.6947 4584.626) (9752.6718 4586.626) (9752.1221 4591.145) (9751.2977 4597.1603)
      (9749.7099 4603.1756) (9747.2672 4607.5878) (9744.2748 4609.2061) (9741.2824 4607.5878) (9738.8397 4603.1756)
      (9737.2519 4597.1603) (9736.4427 4591.145) (9735.8779 4586.626) (9734.855 4584.626) (9732.7176 4585.3282)
      (9729.1298 4588.1221) (9724.2901 4591.7863) (9718.916 4594.9313) (9714.0763 4596.3206) (9710.8092 4595.3435)
      (9709.8321 4592.0916) (9711.2366 4587.2366) (9714.3664 4581.8626) (9718.0458 4577.0229) (9720.8397 4573.4351)
      (9721.542 4571.2977) (9719.5267 4570.2901) (9715.0229 4569.7252) (9708.9924 4568.9008) (9702.9771 4567.313)
      (9698.5649 4564.8855)
    ))
    ; P2731 -- see feature_dimensions_mm.csv
    ("06_ORNAMENT" 1 (
      (9696.9466 4271.8015) (9698.5649 4268.8092) (9702.9771 4266.3664) (9708.9924 4264.7939) (9715.0229 4263.9695)
      (9719.5267 4263.4046) (9721.542 4262.3817) (9720.8397 4260.2443) (9718.0458 4256.6565) (9714.3664 4251.8168)
      (9711.2366 4246.458) (9709.8321 4241.6031) (9710.8092 4238.3359) (9714.0763 4237.374) (9718.916 4238.7634)
      (9724.2901 4241.8931) (9729.1298 4245.5725) (9732.7176 4248.3664) (9734.855 4249.0687) (9735.8779 4247.0687)
      (9736.4427 4242.5496) (9737.2519 4236.5344) (9738.8397 4230.5191) (9741.2824 4226.0916) (9744.2748 4224.4733)
      (9747.2672 4226.0916) (9749.7099 4230.5191) (9751.2977 4236.5344) (9752.1221 4242.5496) (9752.6718 4247.0687)
      (9753.6947 4249.0687) (9755.8321 4248.3664) (9759.4198 4245.5725) (9764.2595 4241.8931) (9769.6336 4238.7634)
      (9774.4733 4237.374) (9777.7405 4238.3359) (9778.7176 4241.6031) (9777.313 4246.458) (9774.1832 4251.8168)
      (9770.5038 4256.6565) (9767.7099 4260.2443) (9767.0076 4262.3817) (9769.0229 4263.4046) (9773.5267 4263.9695)
      (9779.5573 4264.7939) (9785.5725 4266.3664) (9789.9847 4268.8092) (9791.6031 4271.8015) (9789.9847 4274.8092)
      (9785.5725 4277.2366) (9779.5573 4278.8244) (9773.5267 4279.6489) (9769.0229 4280.2137) (9767.0076 4281.2214)
      (9767.7099 4283.3588) (9770.5038 4286.9466) (9774.1832 4291.7863) (9777.313 4297.1603) (9778.7176 4302.0153)
      (9777.7405 4305.2672) (9774.4733 4306.2443) (9769.6336 4304.855) (9764.2595 4301.7099) (9759.4198 4298.0458)
      (9755.8321 4295.2519) (9753.6947 4294.5496) (9752.6718 4296.5496) (9752.1221 4301.0687) (9751.2977 4307.084)
      (9749.7099 4313.0992) (9747.2672 4317.5115) (9744.2748 4319.1298) (9741.2824 4317.5115) (9738.8397 4313.0992)
      (9737.2519 4307.084) (9736.4427 4301.0687) (9735.8779 4296.5496) (9734.855 4294.5496) (9732.7176 4295.2519)
      (9729.1298 4298.0458) (9724.2901 4301.7099) (9718.916 4304.855) (9714.0763 4306.2443) (9710.8092 4305.2672)
      (9709.8321 4302.0153) (9711.2366 4297.1603) (9714.3664 4291.7863) (9718.0458 4286.9466) (9720.8397 4283.3588)
      (9721.542 4281.2214) (9719.5267 4280.2137) (9715.0229 4279.6489) (9708.9924 4278.8244) (9702.9771 4277.2366)
      (9698.5649 4274.8092)
    ))
    ; P2732 -- see feature_dimensions_mm.csv
    ("06_ORNAMENT" 1 (
      (9696.9466 3981.7252) (9698.5649 3978.7328) (9702.9771 3976.2901) (9708.9924 3974.7176) (9715.0229 3973.8931)
      (9719.5267 3973.3282) (9721.542 3972.3053) (9720.8397 3970.1679) (9718.0458 3966.5802) (9714.3664 3961.7405)
      (9711.2366 3956.3817) (9709.8321 3951.5267) (9710.8092 3948.2595) (9714.0763 3947.2977) (9718.916 3948.687)
      (9724.2901 3951.8168) (9729.1298 3955.4962) (9732.7176 3958.2901) (9734.855 3958.9924) (9735.8779 3956.9924)
      (9736.4427 3952.4733) (9737.2519 3946.458) (9738.8397 3940.4427) (9741.2824 3936.0153) (9744.2748 3934.3969)
      (9747.2672 3936.0153) (9749.7099 3940.4427) (9751.2977 3946.458) (9752.1221 3952.4733) (9752.6718 3956.9924)
      (9753.6947 3958.9924) (9755.8321 3958.2901) (9759.4198 3955.4962) (9764.2595 3951.8168) (9769.6336 3948.687)
      (9774.4733 3947.2977) (9777.7405 3948.2595) (9778.7176 3951.5267) (9777.313 3956.3817) (9774.1832 3961.7405)
      (9770.5038 3966.5802) (9767.7099 3970.1679) (9767.0076 3972.3053) (9769.0229 3973.3282) (9773.5267 3973.8931)
      (9779.5573 3974.7176) (9785.5725 3976.2901) (9789.9847 3978.7328) (9791.6031 3981.7252) (9789.9847 3984.7328)
      (9785.5725 3987.1603) (9779.5573 3988.7481) (9773.5267 3989.5725) (9769.0229 3990.1374) (9767.0076 3991.145)
      (9767.7099 3993.2824) (9770.5038 3996.8702) (9774.1832 4001.7099) (9777.313 4007.084) (9778.7176 4011.9389)
      (9777.7405 4015.1908) (9774.4733 4016.1679) (9769.6336 4014.7786) (9764.2595 4011.6336) (9759.4198 4007.9695)
      (9755.8321 4005.1756) (9753.6947 4004.4733) (9752.6718 4006.4733) (9752.1221 4010.9924) (9751.2977 4017.0076)
      (9749.7099 4023.0229) (9747.2672 4027.4351) (9744.2748 4029.0534) (9741.2824 4027.4351) (9738.8397 4023.0229)
      (9737.2519 4017.0076) (9736.4427 4010.9924) (9735.8779 4006.4733) (9734.855 4004.4733) (9732.7176 4005.1756)
      (9729.1298 4007.9695) (9724.2901 4011.6336) (9718.916 4014.7786) (9714.0763 4016.1679) (9710.8092 4015.1908)
      (9709.8321 4011.9389) (9711.2366 4007.084) (9714.3664 4001.7099) (9718.0458 3996.8702) (9720.8397 3993.2824)
      (9721.542 3991.145) (9719.5267 3990.1374) (9715.0229 3989.5725) (9708.9924 3988.7481) (9702.9771 3987.1603)
      (9698.5649 3984.7328)
    ))
    ; P2733 -- see feature_dimensions_mm.csv
    ("06_ORNAMENT" 1 (
      (9715.2824 2782.8244) (9748.0763 2768.6718) (9769.0229 2758.9313) (9772.1832 2765.4198) (9784.4122 2795.9389)
      (9794.9618 2827.8473) (9803.8321 2860.687) (9811.0534 2893.9542) (9816.6412 2927.2061) (9820.6107 2959.9237)
      (9822.9771 2991.6794) (9823.7405 3020.7939) (9825.8779 3020.1527) (9835.1756 3018.4885) (9843.1756 3017.4809)
      (9848.9008 3016.3664) (9851.8779 3014.3511) (9852.1374 3010.7786) (9850.229 3005.2519) (9847.1145 2997.8168)
      (9843.9084 2988.9466) (9841.6794 2979.4962) (9841.2824 2970.5954) (9843.1603 2963.3893) (9847.3282 2958.8397)
      (9849.6183 2958.3359) (9840.5191 2935.2214) (9832.7481 2911.3435) (9826.5038 2887.0534) (9821.9695 2862.5954)
      (9819.374 2838.2748) (9818.8855 2814.3969) (9820.7023 2791.2061) (9825.0382 2769.0076) (9832.0611 2748.0916)
      (9848.4275 2764.5038) (9862.9618 2783.1908) (9875.7405 2803.8015) (9886.7634 2825.9695) (9896.0916 2849.3435)
      (9903.7252 2873.5267) (9909.7099 2898.1985) (9914.0916 2922.9618) (9916.9008 2947.4656) (9917.8015 2964.6565)
      (9918.2137 2964.2748) (9925.7252 2959.4809) (9932.9008 2957.5115) (9938.9313 2958.8397) (9943.0992 2963.3893)
      (9944.9771 2970.5954) (9944.5802 2979.4962) (9942.3511 2988.9466) (9939.145 2997.8168) (9936.0305 3005.2519)
      (9934.1221 3010.7786) (9934.3817 3014.3511) (9937.3588 3016.3664) (9943.084 3017.4809) (9951.084 3018.4885)
      (9960.3817 3020.1527) (9969.6641 3022.9466) (9977.5725 3027.0534) (9982.8702 3032.2901) (9984.7328 3038.1679)
      (9982.8702 3044.0458) (9977.5725 3049.2824) (9969.6641 3053.3893) (9960.3817 3056.1832) (9951.084 3057.8473)
      (9943.084 3058.855) (9937.3588 3059.9695) (9934.3817 3061.9847) (9934.1221 3065.5573) (9936.0305 3071.084)
      (9939.145 3078.5191) (9942.3511 3087.3893) (9944.5802 3096.8397) (9944.9771 3105.7405) (9943.0992 3112.9466)
      (9938.9313 3117.4962) (9932.9008 3118.8244) (9925.7252 3116.855) (9918.2137 3112.0611) (9911.145 3105.4198)
      (9905.0687 3098.1985) (9900.1832 3091.771) (9896.3511 3087.374) (9893.1298 3085.8015) (9889.9084 3087.374)
      (9886.0763 3091.771) (9881.1908 3098.1985) (9875.1145 3105.4198) (9868.0458 3112.0611) (9860.5344 3116.855)
      (9853.3588 3118.8244) (9847.3282 3117.4962) (9843.1603 3112.9466) (9841.2824 3105.7405) (9841.6794 3096.8397)
      (9843.9084 3087.3893) (9847.1145 3078.5191) (9850.229 3071.084) (9852.1374 3065.5573) (9851.8779 3061.9847)
      (9848.9008 3059.9695) (9843.1756 3058.855) (9835.1756 3057.8473) (9825.8779 3056.1832) (9822.5496 3055.1756)
      (9820.6565 3076.2137) (9816.7939 3099.2366) (9803.0076 3077.6183) (9789.4962 3053.1908) (9776.458 3026.3817)
      (9764.1069 2997.5725) (9752.6565 2967.1603) (9742.3359 2935.542) (9733.3282 2903.1145) (9725.8626 2870.2901)
      (9720.1527 2837.4504) (9716.3969 2805.0076)
    ))
    ; P2734 -- see feature_dimensions_mm.csv
    ("06_ORNAMENT" 1 (
      (9725.9542 5214.5496) (9744.2748 5193.9389) (9762.5954 5214.5496) (9744.2748 5235.1603)
    ))
    ; P2735 -- see feature_dimensions_mm.csv
    ("06_ORNAMENT" 1 (
      (9725.9542 4924.4733) (9744.2748 4903.8626) (9762.5954 4924.4733) (9744.2748 4945.084)
    ))
    ; P2736 -- see feature_dimensions_mm.csv
    ("06_ORNAMENT" 1 (
      (9725.9542 4634.3969) (9744.2748 4613.7863) (9762.5954 4634.3969) (9744.2748 4655.0076)
    ))
    ; P2737 -- see feature_dimensions_mm.csv
    ("06_ORNAMENT" 1 (
      (9725.9542 4344.3206) (9744.2748 4323.7099) (9762.5954 4344.3206) (9744.2748 4364.9313)
    ))
    ; P2738 -- see feature_dimensions_mm.csv
    ("06_ORNAMENT" 1 (
      (9725.9542 4054.2443) (9744.2748 4033.6336) (9762.5954 4054.2443) (9744.2748 4074.855)
    ))
    ; P2739 -- see feature_dimensions_mm.csv
    ("06_ORNAMENT" 1 (
      (9732.3664 5432.1069) (9733.2672 5427.5573) (9735.8473 5423.6947) (9739.7252 5421.1145) (9744.2748 5420.1985)
      (9748.8244 5421.1145) (9752.7023 5423.6947) (9755.2824 5427.5573) (9756.1832 5432.1069) (9755.2824 5436.6718)
      (9752.7023 5440.5344) (9748.8244 5443.1145) (9744.2748 5444.0153) (9739.7252 5443.1145) (9735.8473 5440.5344)
      (9733.2672 5436.6718)
    ))
    ; P2740 -- see feature_dimensions_mm.csv
    ("06_ORNAMENT" 1 (
      (9732.3664 5142.0305) (9733.2672 5137.4809) (9735.8473 5133.6183) (9739.7252 5131.0382) (9744.2748 5130.1221)
      (9748.8244 5131.0382) (9752.7023 5133.6183) (9755.2824 5137.4809) (9756.1832 5142.0305) (9755.2824 5146.5954)
      (9752.7023 5150.458) (9748.8244 5153.0382) (9744.2748 5153.9389) (9739.7252 5153.0382) (9735.8473 5150.458)
      (9733.2672 5146.5954)
    ))
    ; P2741 -- see feature_dimensions_mm.csv
    ("06_ORNAMENT" 1 (
      (9732.3664 4851.9542) (9733.2672 4847.4046) (9735.8473 4843.542) (9739.7252 4840.9618) (9744.2748 4840.0458)
      (9748.8244 4840.9618) (9752.7023 4843.542) (9755.2824 4847.4046) (9756.1832 4851.9542) (9755.2824 4856.5191)
      (9752.7023 4860.3817) (9748.8244 4862.9618) (9744.2748 4863.8626) (9739.7252 4862.9618) (9735.8473 4860.3817)
      (9733.2672 4856.5191)
    ))
    ; P2742 -- see feature_dimensions_mm.csv
    ("06_ORNAMENT" 1 (
      (9732.3664 4561.8779) (9733.2672 4557.3282) (9735.8473 4553.4656) (9739.7252 4550.8855) (9744.2748 4549.9695)
      (9748.8244 4550.8855) (9752.7023 4553.4656) (9755.2824 4557.3282) (9756.1832 4561.8779) (9755.2824 4566.4427)
      (9752.7023 4570.3053) (9748.8244 4572.8855) (9744.2748 4573.7863) (9739.7252 4572.8855) (9735.8473 4570.3053)
      (9733.2672 4566.4427)
    ))
    ; P2743 -- see feature_dimensions_mm.csv
    ("06_ORNAMENT" 1 (
      (9732.3664 4271.8015) (9733.2672 4267.2519) (9735.8473 4263.3893) (9739.7252 4260.8092) (9744.2748 4259.8931)
      (9748.8244 4260.8092) (9752.7023 4263.3893) (9755.2824 4267.2519) (9756.1832 4271.8015) (9755.2824 4276.3664)
      (9752.7023 4280.229) (9748.8244 4282.8092) (9744.2748 4283.7099) (9739.7252 4282.8092) (9735.8473 4280.229)
      (9733.2672 4276.3664)
    ))
    ; P2744 -- see feature_dimensions_mm.csv
    ("06_ORNAMENT" 1 (
      (9732.3664 3981.7252) (9733.2672 3977.1756) (9735.8473 3973.313) (9739.7252 3970.7328) (9744.2748 3969.8168)
      (9748.8244 3970.7328) (9752.7023 3973.313) (9755.2824 3977.1756) (9756.1832 3981.7252) (9755.2824 3986.2901)
      (9752.7023 3990.1527) (9748.8244 3992.7328) (9744.2748 3993.6336) (9739.7252 3992.7328) (9735.8473 3990.1527)
      (9733.2672 3986.2901)
    ))
    ; P2745 -- see feature_dimensions_mm.csv
    ("06_ORNAMENT" 1 (
      (9769.4656 5287.0687) (9771.084 5284.0763) (9775.4962 5281.6336) (9781.5115 5280.0611) (9787.542 5279.2366)
      (9792.0458 5278.6718) (9794.0611 5277.6489) (9793.3588 5275.5115) (9790.5649 5271.9237) (9786.8855 5267.084)
      (9783.7557 5261.7252) (9782.3511 5256.8702) (9783.3282 5253.6031) (9786.5954 5252.6412) (9791.4351 5254.0305)
      (9796.8092 5257.1603) (9801.6489 5260.8397) (9805.2366 5263.6336) (9807.374 5264.3359) (9808.3969 5262.3359)
      (9808.9618 5257.8168) (9809.771 5251.8015) (9811.3588 5245.7863) (9813.8015 5241.3588) (9816.7939 5239.7405)
      (9819.7863 5241.3588) (9822.229 5245.7863) (9823.8168 5251.8015) (9824.6412 5257.8168) (9825.1908 5262.3359)
      (9826.2137 5264.3359) (9828.3511 5263.6336) (9831.9389 5260.8397) (9836.7786 5257.1603) (9842.1527 5254.0305)
      (9846.9924 5252.6412) (9850.2595 5253.6031) (9851.2366 5256.8702) (9849.8321 5261.7252) (9846.7023 5267.084)
      (9843.0229 5271.9237) (9840.229 5275.5115) (9839.5267 5277.6489) (9841.542 5278.6718) (9846.0458 5279.2366)
      (9852.0763 5280.0611) (9858.0916 5281.6336) (9862.5038 5284.0763) (9864.1221 5287.0687) (9862.5038 5290.0763)
      (9858.0916 5292.5038) (9852.0763 5294.0916) (9846.0458 5294.916) (9841.542 5295.4809) (9839.5267 5296.4885)
      (9840.229 5298.626) (9843.0229 5302.2137) (9846.7023 5307.0534) (9849.8321 5312.4275) (9851.2366 5317.2824)
      (9850.2595 5320.5344) (9846.9924 5321.5115) (9842.1527 5320.1221) (9836.7786 5316.9771) (9831.9389 5313.313)
      (9828.3511 5310.5191) (9826.2137 5309.8168) (9825.1908 5311.8168) (9824.6412 5316.3359) (9823.8168 5322.3511)
      (9822.229 5328.3664) (9819.7863 5332.7786) (9816.7939 5334.3969) (9813.8015 5332.7786) (9811.3588 5328.3664)
      (9809.771 5322.3511) (9808.9618 5316.3359) (9808.3969 5311.8168) (9807.374 5309.8168) (9805.2366 5310.5191)
      (9801.6489 5313.313) (9796.8092 5316.9771) (9791.4351 5320.1221) (9786.5954 5321.5115) (9783.3282 5320.5344)
      (9782.3511 5317.2824) (9783.7557 5312.4275) (9786.8855 5307.0534) (9790.5649 5302.2137) (9793.3588 5298.626)
      (9794.0611 5296.4885) (9792.0458 5295.4809) (9787.542 5294.916) (9781.5115 5294.0916) (9775.4962 5292.5038)
      (9771.084 5290.0763)
    ))
    ; P2746 -- see feature_dimensions_mm.csv
    ("06_ORNAMENT" 1 (
      (9769.4656 4996.9924) (9771.084 4994.0) (9775.4962 4991.5573) (9781.5115 4989.9847) (9787.542 4989.1603)
      (9792.0458 4988.5954) (9794.0611 4987.5725) (9793.3588 4985.4351) (9790.5649 4981.8473) (9786.8855 4977.0076)
      (9783.7557 4971.6489) (9782.3511 4966.7939) (9783.3282 4963.5267) (9786.5954 4962.5649) (9791.4351 4963.9542)
      (9796.8092 4967.084) (9801.6489 4970.7634) (9805.2366 4973.5573) (9807.374 4974.2595) (9808.3969 4972.2595)
      (9808.9618 4967.7405) (9809.771 4961.7252) (9811.3588 4955.7099) (9813.8015 4951.2824) (9816.7939 4949.6641)
      (9819.7863 4951.2824) (9822.229 4955.7099) (9823.8168 4961.7252) (9824.6412 4967.7405) (9825.1908 4972.2595)
      (9826.2137 4974.2595) (9828.3511 4973.5573) (9831.9389 4970.7634) (9836.7786 4967.084) (9842.1527 4963.9542)
      (9846.9924 4962.5649) (9850.2595 4963.5267) (9851.2366 4966.7939) (9849.8321 4971.6489) (9846.7023 4977.0076)
      (9843.0229 4981.8473) (9840.229 4985.4351) (9839.5267 4987.5725) (9841.542 4988.5954) (9846.0458 4989.1603)
      (9852.0763 4989.9847) (9858.0916 4991.5573) (9862.5038 4994.0) (9864.1221 4996.9924) (9862.5038 5000.0)
      (9858.0916 5002.4275) (9852.0763 5004.0153) (9846.0458 5004.8397) (9841.542 5005.4046) (9839.5267 5006.4122)
      (9840.229 5008.5496) (9843.0229 5012.1374) (9846.7023 5016.9771) (9849.8321 5022.3511) (9851.2366 5027.2061)
      (9850.2595 5030.458) (9846.9924 5031.4351) (9842.1527 5030.0458) (9836.7786 5026.9008) (9831.9389 5023.2366)
      (9828.3511 5020.4427) (9826.2137 5019.7405) (9825.1908 5021.7405) (9824.6412 5026.2595) (9823.8168 5032.2748)
      (9822.229 5038.2901) (9819.7863 5042.7023) (9816.7939 5044.3206) (9813.8015 5042.7023) (9811.3588 5038.2901)
      (9809.771 5032.2748) (9808.9618 5026.2595) (9808.3969 5021.7405) (9807.374 5019.7405) (9805.2366 5020.4427)
      (9801.6489 5023.2366) (9796.8092 5026.9008) (9791.4351 5030.0458) (9786.5954 5031.4351) (9783.3282 5030.458)
      (9782.3511 5027.2061) (9783.7557 5022.3511) (9786.8855 5016.9771) (9790.5649 5012.1374) (9793.3588 5008.5496)
      (9794.0611 5006.4122) (9792.0458 5005.4046) (9787.542 5004.8397) (9781.5115 5004.0153) (9775.4962 5002.4275)
      (9771.084 5000.0)
    ))
    ; P2747 -- see feature_dimensions_mm.csv
    ("06_ORNAMENT" 1 (
      (9769.4656 4706.916) (9771.084 4703.9237) (9775.4962 4701.4809) (9781.5115 4699.9084) (9787.542 4699.084)
      (9792.0458 4698.5191) (9794.0611 4697.4962) (9793.3588 4695.3588) (9790.5649 4691.771) (9786.8855 4686.9313)
      (9783.7557 4681.5725) (9782.3511 4676.7176) (9783.3282 4673.4504) (9786.5954 4672.4885) (9791.4351 4673.8779)
      (9796.8092 4677.0076) (9801.6489 4680.687) (9805.2366 4683.4809) (9807.374 4684.1832) (9808.3969 4682.1832)
      (9808.9618 4677.6641) (9809.771 4671.6489) (9811.3588 4665.6336) (9813.8015 4661.2061) (9816.7939 4659.5878)
      (9819.7863 4661.2061) (9822.229 4665.6336) (9823.8168 4671.6489) (9824.6412 4677.6641) (9825.1908 4682.1832)
      (9826.2137 4684.1832) (9828.3511 4683.4809) (9831.9389 4680.687) (9836.7786 4677.0076) (9842.1527 4673.8779)
      (9846.9924 4672.4885) (9850.2595 4673.4504) (9851.2366 4676.7176) (9849.8321 4681.5725) (9846.7023 4686.9313)
      (9843.0229 4691.771) (9840.229 4695.3588) (9839.5267 4697.4962) (9841.542 4698.5191) (9846.0458 4699.084)
      (9852.0763 4699.9084) (9858.0916 4701.4809) (9862.5038 4703.9237) (9864.1221 4706.916) (9862.5038 4709.9237)
      (9858.0916 4712.3511) (9852.0763 4713.9389) (9846.0458 4714.7634) (9841.542 4715.3282) (9839.5267 4716.3359)
      (9840.229 4718.4733) (9843.0229 4722.0611) (9846.7023 4726.9008) (9849.8321 4732.2748) (9851.2366 4737.1298)
      (9850.2595 4740.3817) (9846.9924 4741.3588) (9842.1527 4739.9695) (9836.7786 4736.8244) (9831.9389 4733.1603)
      (9828.3511 4730.3664) (9826.2137 4729.6641) (9825.1908 4731.6641) (9824.6412 4736.1832) (9823.8168 4742.1985)
      (9822.229 4748.2137) (9819.7863 4752.626) (9816.7939 4754.2443) (9813.8015 4752.626) (9811.3588 4748.2137)
      (9809.771 4742.1985) (9808.9618 4736.1832) (9808.3969 4731.6641) (9807.374 4729.6641) (9805.2366 4730.3664)
      (9801.6489 4733.1603) (9796.8092 4736.8244) (9791.4351 4739.9695) (9786.5954 4741.3588) (9783.3282 4740.3817)
      (9782.3511 4737.1298) (9783.7557 4732.2748) (9786.8855 4726.9008) (9790.5649 4722.0611) (9793.3588 4718.4733)
      (9794.0611 4716.3359) (9792.0458 4715.3282) (9787.542 4714.7634) (9781.5115 4713.9389) (9775.4962 4712.3511)
      (9771.084 4709.9237)
    ))
    ; P2748 -- see feature_dimensions_mm.csv
    ("06_ORNAMENT" 1 (
      (9769.4656 4126.7634) (9771.084 4123.771) (9775.4962 4121.3282) (9781.5115 4119.7557) (9787.542 4118.9313)
      (9792.0458 4118.3664) (9794.0611 4117.3435) (9793.3588 4115.2061) (9790.5649 4111.6183) (9786.8855 4106.7786)
      (9783.7557 4101.4198) (9782.3511 4096.5649) (9783.3282 4093.2977) (9786.5954 4092.3359) (9791.4351 4093.7252)
      (9796.8092 4096.855) (9801.6489 4100.5344) (9805.2366 4103.3282) (9807.374 4104.0305) (9808.3969 4102.0305)
      (9808.9618 4097.5115) (9809.771 4091.4962) (9811.3588 4085.4809) (9813.8015 4081.0534) (9816.7939 4079.4351)
      (9819.7863 4081.0534) (9822.229 4085.4809) (9823.8168 4091.4962) (9824.6412 4097.5115) (9825.1908 4102.0305)
      (9826.2137 4104.0305) (9828.3511 4103.3282) (9831.9389 4100.5344) (9836.7786 4096.855) (9842.1527 4093.7252)
      (9846.9924 4092.3359) (9850.2595 4093.2977) (9851.2366 4096.5649) (9849.8321 4101.4198) (9846.7023 4106.7786)
      (9843.0229 4111.6183) (9840.229 4115.2061) (9839.5267 4117.3435) (9841.542 4118.3664) (9846.0458 4118.9313)
      (9852.0763 4119.7557) (9858.0916 4121.3282) (9862.5038 4123.771) (9864.1221 4126.7634) (9862.5038 4129.771)
      (9858.0916 4132.1985) (9852.0763 4133.7863) (9846.0458 4134.6107) (9841.542 4135.1756) (9839.5267 4136.1832)
      (9840.229 4138.3206) (9843.0229 4141.9084) (9846.7023 4146.7481) (9849.8321 4152.1221) (9851.2366 4156.9771)
      (9850.2595 4160.229) (9846.9924 4161.2061) (9842.1527 4159.8168) (9836.7786 4156.6718) (9831.9389 4153.0076)
      (9828.3511 4150.2137) (9826.2137 4149.5115) (9825.1908 4151.5115) (9824.6412 4156.0305) (9823.8168 4162.0458)
      (9822.229 4168.0611) (9819.7863 4172.4733) (9816.7939 4174.0916) (9813.8015 4172.4733) (9811.3588 4168.0611)
      (9809.771 4162.0458) (9808.9618 4156.0305) (9808.3969 4151.5115) (9807.374 4149.5115) (9805.2366 4150.2137)
      (9801.6489 4153.0076) (9796.8092 4156.6718) (9791.4351 4159.8168) (9786.5954 4161.2061) (9783.3282 4160.229)
      (9782.3511 4156.9771) (9783.7557 4152.1221) (9786.8855 4146.7481) (9790.5649 4141.9084) (9793.3588 4138.3206)
      (9794.0611 4136.1832) (9792.0458 4135.1756) (9787.542 4134.6107) (9781.5115 4133.7863) (9775.4962 4132.1985)
      (9771.084 4129.771)
    ))
    ; P2749 -- see feature_dimensions_mm.csv
    ("06_ORNAMENT" 1 (
      (9798.4733 5359.5878) (9816.7939 5338.9771) (9835.1145 5359.5878) (9816.7939 5380.1985)
    ))
    ; P2750 -- see feature_dimensions_mm.csv
    ("06_ORNAMENT" 1 (
      (9798.4733 5069.5115) (9816.7939 5048.9008) (9835.1145 5069.5115) (9816.7939 5090.1221)
    ))
    ; P2751 -- see feature_dimensions_mm.csv
    ("06_ORNAMENT" 1 (
      (9798.4733 4779.4351) (9816.7939 4758.8244) (9835.1145 4779.4351) (9816.7939 4800.0458)
    ))
    ; P2752 -- see feature_dimensions_mm.csv
    ("06_ORNAMENT" 1 (
      (9798.4733 4199.2824) (9816.7939 4178.6718) (9835.1145 4199.2824) (9816.7939 4219.8931)
    ))
    ; P2753 -- see feature_dimensions_mm.csv
    ("06_ORNAMENT" 1 (
      (9798.4733 3909.2061) (9816.7939 3888.5954) (9835.1145 3909.2061) (9816.7939 3929.8168)
    ))
    ; P2754 -- see feature_dimensions_mm.csv
    ("06_ORNAMENT" 1 (
      (9804.8855 5287.0687) (9805.7863 5282.5191) (9808.3664 5278.6565) (9812.2443 5276.0763) (9816.7939 5275.1603)
      (9821.3435 5276.0763) (9825.2214 5278.6565) (9827.8015 5282.5191) (9828.7023 5287.0687) (9827.8015 5291.6336)
      (9825.2214 5295.4962) (9821.3435 5298.0763) (9816.7939 5298.9771) (9812.2443 5298.0763) (9808.3664 5295.4962)
      (9805.7863 5291.6336)
    ))
    ; P2755 -- see feature_dimensions_mm.csv
    ("06_ORNAMENT" 1 (
      (9804.8855 4996.9924) (9805.7863 4992.4427) (9808.3664 4988.5802) (9812.2443 4986.0) (9816.7939 4985.084)
      (9821.3435 4986.0) (9825.2214 4988.5802) (9827.8015 4992.4427) (9828.7023 4996.9924) (9827.8015 5001.5573)
      (9825.2214 5005.4198) (9821.3435 5008.0) (9816.7939 5008.9008) (9812.2443 5008.0) (9808.3664 5005.4198)
      (9805.7863 5001.5573)
    ))
    ; P2756 -- see feature_dimensions_mm.csv
    ("06_ORNAMENT" 1 (
      (9804.8855 4706.916) (9805.7863 4702.3664) (9808.3664 4698.5038) (9812.2443 4695.9237) (9816.7939 4695.0076)
      (9821.3435 4695.9237) (9825.2214 4698.5038) (9827.8015 4702.3664) (9828.7023 4706.916) (9827.8015 4711.4809)
      (9825.2214 4715.3435) (9821.3435 4717.9237) (9816.7939 4718.8244) (9812.2443 4717.9237) (9808.3664 4715.3435)
      (9805.7863 4711.4809)
    ))
    ; P2757 -- see feature_dimensions_mm.csv
    ("06_ORNAMENT" 1 (
      (9804.8855 4126.7634) (9805.7863 4122.2137) (9808.3664 4118.3511) (9812.2443 4115.771) (9816.7939 4114.855)
      (9821.3435 4115.771) (9825.2214 4118.3511) (9827.8015 4122.2137) (9828.7023 4126.7634) (9827.8015 4131.3282)
      (9825.2214 4135.1908) (9821.3435 4137.771) (9816.7939 4138.6718) (9812.2443 4137.771) (9808.3664 4135.1908)
      (9805.7863 4131.3282)
    ))
    ; P2758 -- see feature_dimensions_mm.csv
    ("06_ORNAMENT" 1 (
      (9841.9847 5142.0305) (9843.6031 5139.0382) (9848.0153 5136.5954) (9854.0305 5135.0229) (9860.0611 5134.1985)
      (9864.5649 5133.6336) (9866.5802 5132.6107) (9865.8779 5130.4733) (9863.084 5126.8855) (9859.4046 5122.0458)
      (9856.2748 5116.687) (9854.8702 5111.8321) (9855.8473 5108.5649) (9859.1145 5107.6031) (9863.9542 5108.9924)
      (9869.3282 5112.1221) (9874.1679 5115.8015) (9877.7557 5118.5954) (9879.8931 5119.2977) (9880.916 5117.2977)
      (9881.4809 5112.7786) (9882.2901 5106.7634) (9883.8779 5100.7481) (9886.3206 5096.3206) (9889.313 5094.7023)
      (9892.3053 5096.3206) (9894.7481 5100.7481) (9896.3359 5106.7634) (9897.1603 5112.7786) (9897.7099 5117.2977)
      (9898.7328 5119.2977) (9900.8702 5118.5954) (9904.458 5115.8015) (9909.2977 5112.1221) (9914.6718 5108.9924)
      (9919.5115 5107.6031) (9922.7786 5108.5649) (9923.7557 5111.8321) (9922.3511 5116.687) (9919.2214 5122.0458)
      (9915.542 5126.8855) (9912.7481 5130.4733) (9912.0458 5132.6107) (9914.0611 5133.6336) (9918.5649 5134.1985)
      (9924.5954 5135.0229) (9930.6107 5136.5954) (9935.0229 5139.0382) (9936.6412 5142.0305) (9935.0229 5145.0382)
      (9930.6107 5147.4656) (9924.5954 5149.0534) (9918.5649 5149.8779) (9914.0611 5150.4427) (9912.0458 5151.4504)
      (9912.7481 5153.5878) (9915.542 5157.1756) (9919.2214 5162.0153) (9922.3511 5167.3893) (9923.7557 5172.2443)
      (9922.7786 5175.4962) (9919.5115 5176.4733) (9914.6718 5175.084) (9909.2977 5171.9389) (9904.458 5168.2748)
      (9900.8702 5165.4809) (9898.7328 5164.7786) (9897.7099 5166.7786) (9897.1603 5171.2977) (9896.3359 5177.313)
      (9894.7481 5183.3282) (9892.3053 5187.7405) (9889.313 5189.3588) (9886.3206 5187.7405) (9883.8779 5183.3282)
      (9882.2901 5177.313) (9881.4809 5171.2977) (9880.916 5166.7786) (9879.8931 5164.7786) (9877.7557 5165.4809)
      (9874.1679 5168.2748) (9869.3282 5171.9389) (9863.9542 5175.084) (9859.1145 5176.4733) (9855.8473 5175.4962)
      (9854.8702 5172.2443) (9856.2748 5167.3893) (9859.4046 5162.0153) (9863.084 5157.1756) (9865.8779 5153.5878)
      (9866.5802 5151.4504) (9864.5649 5150.4427) (9860.0611 5149.8779) (9854.0305 5149.0534) (9848.0153 5147.4656)
      (9843.6031 5145.0382)
    ))
    ; P2759 -- see feature_dimensions_mm.csv
    ("06_ORNAMENT" 1 (
      (9841.9847 4851.9542) (9843.6031 4848.9618) (9848.0153 4846.5191) (9854.0305 4844.9466) (9860.0611 4844.1221)
      (9864.5649 4843.5573) (9866.5802 4842.5344) (9865.8779 4840.3969) (9863.084 4836.8092) (9859.4046 4831.9695)
      (9856.2748 4826.6107) (9854.8702 4821.7557) (9855.8473 4818.4885) (9859.1145 4817.5267) (9863.9542 4818.916)
      (9869.3282 4822.0458) (9874.1679 4825.7252) (9877.7557 4828.5191) (9879.8931 4829.2214) (9880.916 4827.2214)
      (9881.4809 4822.7023) (9882.2901 4816.687) (9883.8779 4810.6718) (9886.3206 4806.2443) (9889.313 4804.626)
      (9892.3053 4806.2443) (9894.7481 4810.6718) (9896.3359 4816.687) (9897.1603 4822.7023) (9897.7099 4827.2214)
      (9898.7328 4829.2214) (9900.8702 4828.5191) (9904.458 4825.7252) (9909.2977 4822.0458) (9914.6718 4818.916)
      (9919.5115 4817.5267) (9922.7786 4818.4885) (9923.7557 4821.7557) (9922.3511 4826.6107) (9919.2214 4831.9695)
      (9915.542 4836.8092) (9912.7481 4840.3969) (9912.0458 4842.5344) (9914.0611 4843.5573) (9918.5649 4844.1221)
      (9924.5954 4844.9466) (9930.6107 4846.5191) (9935.0229 4848.9618) (9936.6412 4851.9542) (9935.0229 4854.9618)
      (9930.6107 4857.3893) (9924.5954 4858.9771) (9918.5649 4859.8015) (9914.0611 4860.3664) (9912.0458 4861.374)
      (9912.7481 4863.5115) (9915.542 4867.0992) (9919.2214 4871.9389) (9922.3511 4877.313) (9923.7557 4882.1679)
      (9922.7786 4885.4198) (9919.5115 4886.3969) (9914.6718 4885.0076) (9909.2977 4881.8626) (9904.458 4878.1985)
      (9900.8702 4875.4046) (9898.7328 4874.7023) (9897.7099 4876.7023) (9897.1603 4881.2214) (9896.3359 4887.2366)
      (9894.7481 4893.2519) (9892.3053 4897.6641) (9889.313 4899.2824) (9886.3206 4897.6641) (9883.8779 4893.2519)
      (9882.2901 4887.2366) (9881.4809 4881.2214) (9880.916 4876.7023) (9879.8931 4874.7023) (9877.7557 4875.4046)
      (9874.1679 4878.1985) (9869.3282 4881.8626) (9863.9542 4885.0076) (9859.1145 4886.3969) (9855.8473 4885.4198)
      (9854.8702 4882.1679) (9856.2748 4877.313) (9859.4046 4871.9389) (9863.084 4867.0992) (9865.8779 4863.5115)
      (9866.5802 4861.374) (9864.5649 4860.3664) (9860.0611 4859.8015) (9854.0305 4858.9771) (9848.0153 4857.3893)
      (9843.6031 4854.9618)
    ))
    ; P2760 -- see feature_dimensions_mm.csv
    ("06_ORNAMENT" 1 (
      (9841.9847 4561.8779) (9843.6031 4558.8855) (9848.0153 4556.4427) (9854.0305 4554.8702) (9860.0611 4554.0458)
      (9864.5649 4553.4809) (9866.5802 4552.458) (9865.8779 4550.3206) (9863.084 4546.7328) (9859.4046 4541.8931)
      (9856.2748 4536.5344) (9854.8702 4531.6794) (9855.8473 4528.4122) (9859.1145 4527.4504) (9863.9542 4528.8397)
      (9869.3282 4531.9695) (9874.1679 4535.6489) (9877.7557 4538.4427) (9879.8931 4539.145) (9880.916 4537.145)
      (9881.4809 4532.626) (9882.2901 4526.6107) (9883.8779 4520.5954) (9886.3206 4516.1679) (9889.313 4514.5496)
      (9892.3053 4516.1679) (9894.7481 4520.5954) (9896.3359 4526.6107) (9897.1603 4532.626) (9897.7099 4537.145)
      (9898.7328 4539.145) (9900.8702 4538.4427) (9904.458 4535.6489) (9909.2977 4531.9695) (9914.6718 4528.8397)
      (9919.5115 4527.4504) (9922.7786 4528.4122) (9923.7557 4531.6794) (9922.3511 4536.5344) (9919.2214 4541.8931)
      (9915.542 4546.7328) (9912.7481 4550.3206) (9912.0458 4552.458) (9914.0611 4553.4809) (9918.5649 4554.0458)
      (9924.5954 4554.8702) (9930.6107 4556.4427) (9935.0229 4558.8855) (9936.6412 4561.8779) (9935.0229 4564.8855)
      (9930.6107 4567.313) (9924.5954 4568.9008) (9918.5649 4569.7252) (9914.0611 4570.2901) (9912.0458 4571.2977)
      (9912.7481 4573.4351) (9915.542 4577.0229) (9919.2214 4581.8626) (9922.3511 4587.2366) (9923.7557 4592.0916)
      (9922.7786 4595.3435) (9919.5115 4596.3206) (9914.6718 4594.9313) (9909.2977 4591.7863) (9904.458 4588.1221)
      (9900.8702 4585.3282) (9898.7328 4584.626) (9897.7099 4586.626) (9897.1603 4591.145) (9896.3359 4597.1603)
      (9894.7481 4603.1756) (9892.3053 4607.5878) (9889.313 4609.2061) (9886.3206 4607.5878) (9883.8779 4603.1756)
      (9882.2901 4597.1603) (9881.4809 4591.145) (9880.916 4586.626) (9879.8931 4584.626) (9877.7557 4585.3282)
      (9874.1679 4588.1221) (9869.3282 4591.7863) (9863.9542 4594.9313) (9859.1145 4596.3206) (9855.8473 4595.3435)
      (9854.8702 4592.0916) (9856.2748 4587.2366) (9859.4046 4581.8626) (9863.084 4577.0229) (9865.8779 4573.4351)
      (9866.5802 4571.2977) (9864.5649 4570.2901) (9860.0611 4569.7252) (9854.0305 4568.9008) (9848.0153 4567.313)
      (9843.6031 4564.8855)
    ))
    ; P2761 -- see feature_dimensions_mm.csv
    ("06_ORNAMENT" 1 (
      (9841.9847 4271.8015) (9843.6031 4268.8092) (9848.0153 4266.3664) (9854.0305 4264.7939) (9860.0611 4263.9695)
      (9864.5649 4263.4046) (9866.5802 4262.3817) (9865.8779 4260.2443) (9863.084 4256.6565) (9859.4046 4251.8168)
      (9856.2748 4246.458) (9854.8702 4241.6031) (9855.8473 4238.3359) (9859.1145 4237.374) (9863.9542 4238.7634)
      (9869.3282 4241.8931) (9874.1679 4245.5725) (9877.7557 4248.3664) (9879.8931 4249.0687) (9880.916 4247.0687)
      (9881.4809 4242.5496) (9882.2901 4236.5344) (9883.8779 4230.5191) (9886.3206 4226.0916) (9889.313 4224.4733)
      (9892.3053 4226.0916) (9894.7481 4230.5191) (9896.3359 4236.5344) (9897.1603 4242.5496) (9897.7099 4247.0687)
      (9898.7328 4249.0687) (9900.8702 4248.3664) (9904.458 4245.5725) (9909.2977 4241.8931) (9914.6718 4238.7634)
      (9919.5115 4237.374) (9922.7786 4238.3359) (9923.7557 4241.6031) (9922.3511 4246.458) (9919.2214 4251.8168)
      (9915.542 4256.6565) (9912.7481 4260.2443) (9912.0458 4262.3817) (9914.0611 4263.4046) (9918.5649 4263.9695)
      (9924.5954 4264.7939) (9930.6107 4266.3664) (9935.0229 4268.8092) (9936.6412 4271.8015) (9935.0229 4274.8092)
      (9930.6107 4277.2366) (9924.5954 4278.8244) (9918.5649 4279.6489) (9914.0611 4280.2137) (9912.0458 4281.2214)
      (9912.7481 4283.3588) (9915.542 4286.9466) (9919.2214 4291.7863) (9922.3511 4297.1603) (9923.7557 4302.0153)
      (9922.7786 4305.2672) (9919.5115 4306.2443) (9914.6718 4304.855) (9909.2977 4301.7099) (9904.458 4298.0458)
      (9900.8702 4295.2519) (9898.7328 4294.5496) (9897.7099 4296.5496) (9897.1603 4301.0687) (9896.3359 4307.084)
      (9894.7481 4313.0992) (9892.3053 4317.5115) (9889.313 4319.1298) (9886.3206 4317.5115) (9883.8779 4313.0992)
      (9882.2901 4307.084) (9881.4809 4301.0687) (9880.916 4296.5496) (9879.8931 4294.5496) (9877.7557 4295.2519)
      (9874.1679 4298.0458) (9869.3282 4301.7099) (9863.9542 4304.855) (9859.1145 4306.2443) (9855.8473 4305.2672)
      (9854.8702 4302.0153) (9856.2748 4297.1603) (9859.4046 4291.7863) (9863.084 4286.9466) (9865.8779 4283.3588)
      (9866.5802 4281.2214) (9864.5649 4280.2137) (9860.0611 4279.6489) (9854.0305 4278.8244) (9848.0153 4277.2366)
      (9843.6031 4274.8092)
    ))
    ; P2762 -- see feature_dimensions_mm.csv
    ("06_ORNAMENT" 1 (
      (9841.9847 3981.7252) (9843.6031 3978.7328) (9848.0153 3976.2901) (9854.0305 3974.7176) (9860.0611 3973.8931)
      (9864.5649 3973.3282) (9866.5802 3972.3053) (9865.8779 3970.1679) (9863.084 3966.5802) (9859.4046 3961.7405)
      (9856.2748 3956.3817) (9854.8702 3951.5267) (9855.8473 3948.2595) (9859.1145 3947.2977) (9863.9542 3948.687)
      (9869.3282 3951.8168) (9874.1679 3955.4962) (9877.7557 3958.2901) (9879.8931 3958.9924) (9880.916 3956.9924)
      (9881.4809 3952.4733) (9882.2901 3946.458) (9883.8779 3940.4427) (9886.3206 3936.0153) (9889.313 3934.3969)
      (9892.3053 3936.0153) (9894.7481 3940.4427) (9896.3359 3946.458) (9897.1603 3952.4733) (9897.7099 3956.9924)
      (9898.7328 3958.9924) (9900.8702 3958.2901) (9904.458 3955.4962) (9909.2977 3951.8168) (9914.6718 3948.687)
      (9919.5115 3947.2977) (9922.7786 3948.2595) (9923.7557 3951.5267) (9922.3511 3956.3817) (9919.2214 3961.7405)
      (9915.542 3966.5802) (9912.7481 3970.1679) (9912.0458 3972.3053) (9914.0611 3973.3282) (9918.5649 3973.8931)
      (9924.5954 3974.7176) (9930.6107 3976.2901) (9935.0229 3978.7328) (9936.6412 3981.7252) (9935.0229 3984.7328)
      (9930.6107 3987.1603) (9924.5954 3988.7481) (9918.5649 3989.5725) (9914.0611 3990.1374) (9912.0458 3991.145)
      (9912.7481 3993.2824) (9915.542 3996.8702) (9919.2214 4001.7099) (9922.3511 4007.084) (9923.7557 4011.9389)
      (9922.7786 4015.1908) (9919.5115 4016.1679) (9914.6718 4014.7786) (9909.2977 4011.6336) (9904.458 4007.9695)
      (9900.8702 4005.1756) (9898.7328 4004.4733) (9897.7099 4006.4733) (9897.1603 4010.9924) (9896.3359 4017.0076)
      (9894.7481 4023.0229) (9892.3053 4027.4351) (9889.313 4029.0534) (9886.3206 4027.4351) (9883.8779 4023.0229)
      (9882.2901 4017.0076) (9881.4809 4010.9924) (9880.916 4006.4733) (9879.8931 4004.4733) (9877.7557 4005.1756)
      (9874.1679 4007.9695) (9869.3282 4011.6336) (9863.9542 4014.7786) (9859.1145 4016.1679) (9855.8473 4015.1908)
      (9854.8702 4011.9389) (9856.2748 4007.084) (9859.4046 4001.7099) (9863.084 3996.8702) (9865.8779 3993.2824)
      (9866.5802 3991.145) (9864.5649 3990.1374) (9860.0611 3989.5725) (9854.0305 3988.7481) (9848.0153 3987.1603)
      (9843.6031 3984.7328)
    ))
    ; P2763 -- see feature_dimensions_mm.csv
    ("06_ORNAMENT" 1 (
      (9847.3282 7389.313) (9908.3969 7358.7786) (9969.4656 7389.313) (9908.3969 7419.8473)
    ))
    ; P2764 -- see feature_dimensions_mm.csv
    ("06_ORNAMENT" 1 (
      (9847.3282 7297.7099) (9908.3969 7267.1756) (9969.4656 7297.7099) (9908.3969 7328.2443)
    ))
    ; P2765 -- see feature_dimensions_mm.csv
    ("06_ORNAMENT" 1 (
      (9847.3282 7206.1069) (9908.3969 7175.5725) (9969.4656 7206.1069) (9908.3969 7236.6412)
    ))
    ; P2766 -- see feature_dimensions_mm.csv
    ("06_ORNAMENT" 1 (
      (9870.9924 5214.5496) (9889.313 5193.9389) (9907.6336 5214.5496) (9889.313 5235.1603)
    ))
    ; P2767 -- see feature_dimensions_mm.csv
    ("06_ORNAMENT" 1 (
      (9870.9924 4924.4733) (9889.313 4903.8626) (9907.6336 4924.4733) (9889.313 4945.084)
    ))
    ; P2768 -- see feature_dimensions_mm.csv
    ("06_ORNAMENT" 1 (
      (9870.9924 4634.3969) (9889.313 4613.7863) (9907.6336 4634.3969) (9889.313 4655.0076)
    ))
    ; P2769 -- see feature_dimensions_mm.csv
    ("06_ORNAMENT" 1 (
      (9870.9924 4344.3206) (9889.313 4323.7099) (9907.6336 4344.3206) (9889.313 4364.9313)
    ))
    ; P2770 -- see feature_dimensions_mm.csv
    ("06_ORNAMENT" 1 (
      (9870.9924 4054.2443) (9889.313 4033.6336) (9907.6336 4054.2443) (9889.313 4074.855)
    ))
    ; P2771 -- see feature_dimensions_mm.csv
    ("06_ORNAMENT" 1 (
      (9877.4046 5142.0305) (9878.3053 5137.4809) (9880.8855 5133.6183) (9884.7634 5131.0382) (9889.313 5130.1221)
      (9893.8626 5131.0382) (9897.7405 5133.6183) (9900.3206 5137.4809) (9901.2214 5142.0305) (9900.3206 5146.5954)
      (9897.7405 5150.458) (9893.8626 5153.0382) (9889.313 5153.9389) (9884.7634 5153.0382) (9880.8855 5150.458)
      (9878.3053 5146.5954)
    ))
    ; P2772 -- see feature_dimensions_mm.csv
    ("06_ORNAMENT" 1 (
      (9877.4046 4851.9542) (9878.3053 4847.4046) (9880.8855 4843.542) (9884.7634 4840.9618) (9889.313 4840.0458)
      (9893.8626 4840.9618) (9897.7405 4843.542) (9900.3206 4847.4046) (9901.2214 4851.9542) (9900.3206 4856.5191)
      (9897.7405 4860.3817) (9893.8626 4862.9618) (9889.313 4863.8626) (9884.7634 4862.9618) (9880.8855 4860.3817)
      (9878.3053 4856.5191)
    ))
    ; P2773 -- see feature_dimensions_mm.csv
    ("06_ORNAMENT" 1 (
      (9877.4046 4561.8779) (9878.3053 4557.3282) (9880.8855 4553.4656) (9884.7634 4550.8855) (9889.313 4549.9695)
      (9893.8626 4550.8855) (9897.7405 4553.4656) (9900.3206 4557.3282) (9901.2214 4561.8779) (9900.3206 4566.4427)
      (9897.7405 4570.3053) (9893.8626 4572.8855) (9889.313 4573.7863) (9884.7634 4572.8855) (9880.8855 4570.3053)
      (9878.3053 4566.4427)
    ))
    ; P2774 -- see feature_dimensions_mm.csv
    ("06_ORNAMENT" 1 (
      (9877.4046 4271.8015) (9878.3053 4267.2519) (9880.8855 4263.3893) (9884.7634 4260.8092) (9889.313 4259.8931)
      (9893.8626 4260.8092) (9897.7405 4263.3893) (9900.3206 4267.2519) (9901.2214 4271.8015) (9900.3206 4276.3664)
      (9897.7405 4280.229) (9893.8626 4282.8092) (9889.313 4283.7099) (9884.7634 4282.8092) (9880.8855 4280.229)
      (9878.3053 4276.3664)
    ))
    ; P2775 -- see feature_dimensions_mm.csv
    ("06_ORNAMENT" 1 (
      (9877.4046 3981.7252) (9878.3053 3977.1756) (9880.8855 3973.313) (9884.7634 3970.7328) (9889.313 3969.8168)
      (9893.8626 3970.7328) (9897.7405 3973.313) (9900.3206 3977.1756) (9901.2214 3981.7252) (9900.3206 3986.2901)
      (9897.7405 3990.1527) (9893.8626 3992.7328) (9889.313 3993.6336) (9884.7634 3992.7328) (9880.8855 3990.1527)
      (9878.3053 3986.2901)
    ))
    ; P2776 -- see feature_dimensions_mm.csv
    ("06_ORNAMENT" 1 (
      (9914.5038 4996.9924) (9916.1221 4994.0) (9920.5344 4991.5573) (9926.5496 4989.9847) (9932.5802 4989.1603)
      (9937.084 4988.5954) (9939.0992 4987.5725) (9938.3969 4985.4351) (9935.6031 4981.8473) (9931.9237 4977.0076)
      (9928.7939 4971.6489) (9927.3893 4966.7939) (9928.3664 4963.5267) (9931.6336 4962.5649) (9936.4733 4963.9542)
      (9941.8473 4967.084) (9946.687 4970.7634) (9950.2748 4973.5573) (9952.4122 4974.2595) (9953.4351 4972.2595)
      (9954.0 4967.7405) (9954.8092 4961.7252) (9956.3969 4955.7099) (9958.8397 4951.2824) (9961.8321 4949.6641)
      (9964.8244 4951.2824) (9967.2672 4955.7099) (9968.855 4961.7252) (9969.6794 4967.7405) (9970.229 4972.2595)
      (9971.2519 4974.2595) (9973.3893 4973.5573) (9976.9771 4970.7634) (9981.8168 4967.084) (9987.1908 4963.9542)
      (9992.0305 4962.5649) (9995.2977 4963.5267) (9996.2748 4966.7939) (9994.8702 4971.6489) (9991.7405 4977.0076)
      (9988.0611 4981.8473) (9985.2672 4985.4351) (9984.5649 4987.5725) (9986.5802 4988.5954) (9991.084 4989.1603)
      (9997.1145 4989.9847) (10003.1298 4991.5573) (10007.542 4994.0) (10009.1603 4996.9924) (10007.542 5000.0)
      (10003.1298 5002.4275) (9997.1145 5004.0153) (9991.084 5004.8397) (9986.5802 5005.4046) (9984.5649 5006.4122)
      (9985.2672 5008.5496) (9988.0611 5012.1374) (9991.7405 5016.9771) (9994.8702 5022.3511) (9996.2748 5027.2061)
      (9995.2977 5030.458) (9992.0305 5031.4351) (9987.1908 5030.0458) (9981.8168 5026.9008) (9976.9771 5023.2366)
      (9973.3893 5020.4427) (9971.2519 5019.7405) (9970.229 5021.7405) (9969.6794 5026.2595) (9968.855 5032.2748)
      (9967.2672 5038.2901) (9964.8244 5042.7023) (9961.8321 5044.3206) (9958.8397 5042.7023) (9956.3969 5038.2901)
      (9954.8092 5032.2748) (9954.0 5026.2595) (9953.4351 5021.7405) (9952.4122 5019.7405) (9950.2748 5020.4427)
      (9946.687 5023.2366) (9941.8473 5026.9008) (9936.4733 5030.0458) (9931.6336 5031.4351) (9928.3664 5030.458)
      (9927.3893 5027.2061) (9928.7939 5022.3511) (9931.9237 5016.9771) (9935.6031 5012.1374) (9938.3969 5008.5496)
      (9939.0992 5006.4122) (9937.084 5005.4046) (9932.5802 5004.8397) (9926.5496 5004.0153) (9920.5344 5002.4275)
      (9916.1221 5000.0)
    ))
    ; P2777 -- see feature_dimensions_mm.csv
    ("06_ORNAMENT" 1 (
      (9914.5038 4706.916) (9916.1221 4703.9237) (9920.5344 4701.4809) (9926.5496 4699.9084) (9932.5802 4699.084)
      (9937.084 4698.5191) (9939.0992 4697.4962) (9938.3969 4695.3588) (9935.6031 4691.771) (9931.9237 4686.9313)
      (9928.7939 4681.5725) (9927.3893 4676.7176) (9928.3664 4673.4504) (9931.6336 4672.4885) (9936.4733 4673.8779)
      (9941.8473 4677.0076) (9946.687 4680.687) (9950.2748 4683.4809) (9952.4122 4684.1832) (9953.4351 4682.1832)
      (9954.0 4677.6641) (9954.8092 4671.6489) (9956.3969 4665.6336) (9958.8397 4661.2061) (9961.8321 4659.5878)
      (9964.8244 4661.2061) (9967.2672 4665.6336) (9968.855 4671.6489) (9969.6794 4677.6641) (9970.229 4682.1832)
      (9971.2519 4684.1832) (9973.3893 4683.4809) (9976.9771 4680.687) (9981.8168 4677.0076) (9987.1908 4673.8779)
      (9992.0305 4672.4885) (9995.2977 4673.4504) (9996.2748 4676.7176) (9994.8702 4681.5725) (9991.7405 4686.9313)
      (9988.0611 4691.771) (9985.2672 4695.3588) (9984.5649 4697.4962) (9986.5802 4698.5191) (9991.084 4699.084)
      (9997.1145 4699.9084) (10003.1298 4701.4809) (10007.542 4703.9237) (10009.1603 4706.916) (10007.542 4709.9237)
      (10003.1298 4712.3511) (9997.1145 4713.9389) (9991.084 4714.7634) (9986.5802 4715.3282) (9984.5649 4716.3359)
      (9985.2672 4718.4733) (9988.0611 4722.0611) (9991.7405 4726.9008) (9994.8702 4732.2748) (9996.2748 4737.1298)
      (9995.2977 4740.3817) (9992.0305 4741.3588) (9987.1908 4739.9695) (9981.8168 4736.8244) (9976.9771 4733.1603)
      (9973.3893 4730.3664) (9971.2519 4729.6641) (9970.229 4731.6641) (9969.6794 4736.1832) (9968.855 4742.1985)
      (9967.2672 4748.2137) (9964.8244 4752.626) (9961.8321 4754.2443) (9958.8397 4752.626) (9956.3969 4748.2137)
      (9954.8092 4742.1985) (9954.0 4736.1832) (9953.4351 4731.6641) (9952.4122 4729.6641) (9950.2748 4730.3664)
      (9946.687 4733.1603) (9941.8473 4736.8244) (9936.4733 4739.9695) (9931.6336 4741.3588) (9928.3664 4740.3817)
      (9927.3893 4737.1298) (9928.7939 4732.2748) (9931.9237 4726.9008) (9935.6031 4722.0611) (9938.3969 4718.4733)
      (9939.0992 4716.3359) (9937.084 4715.3282) (9932.5802 4714.7634) (9926.5496 4713.9389) (9920.5344 4712.3511)
      (9916.1221 4709.9237)
    ))
    ; P2778 -- see feature_dimensions_mm.csv
    ("06_ORNAMENT" 1 (
      (9914.5038 4126.7634) (9916.1221 4123.771) (9920.5344 4121.3282) (9926.5496 4119.7557) (9932.5802 4118.9313)
      (9937.084 4118.3664) (9939.0992 4117.3435) (9938.3969 4115.2061) (9935.6031 4111.6183) (9931.9237 4106.7786)
      (9928.7939 4101.4198) (9927.3893 4096.5649) (9928.3664 4093.2977) (9931.6336 4092.3359) (9936.4733 4093.7252)
      (9941.8473 4096.855) (9946.687 4100.5344) (9950.2748 4103.3282) (9952.4122 4104.0305) (9953.4351 4102.0305)
      (9954.0 4097.5115) (9954.8092 4091.4962) (9956.3969 4085.4809) (9958.8397 4081.0534) (9961.8321 4079.4351)
      (9964.8244 4081.0534) (9967.2672 4085.4809) (9968.855 4091.4962) (9969.6794 4097.5115) (9970.229 4102.0305)
      (9971.2519 4104.0305) (9973.3893 4103.3282) (9976.9771 4100.5344) (9981.8168 4096.855) (9987.1908 4093.7252)
      (9992.0305 4092.3359) (9995.2977 4093.2977) (9996.2748 4096.5649) (9994.8702 4101.4198) (9991.7405 4106.7786)
      (9988.0611 4111.6183) (9985.2672 4115.2061) (9984.5649 4117.3435) (9986.5802 4118.3664) (9991.084 4118.9313)
      (9997.1145 4119.7557) (10003.1298 4121.3282) (10007.542 4123.771) (10009.1603 4126.7634) (10007.542 4129.771)
      (10003.1298 4132.1985) (9997.1145 4133.7863) (9991.084 4134.6107) (9986.5802 4135.1756) (9984.5649 4136.1832)
      (9985.2672 4138.3206) (9988.0611 4141.9084) (9991.7405 4146.7481) (9994.8702 4152.1221) (9996.2748 4156.9771)
      (9995.2977 4160.229) (9992.0305 4161.2061) (9987.1908 4159.8168) (9981.8168 4156.6718) (9976.9771 4153.0076)
      (9973.3893 4150.2137) (9971.2519 4149.5115) (9970.229 4151.5115) (9969.6794 4156.0305) (9968.855 4162.0458)
      (9967.2672 4168.0611) (9964.8244 4172.4733) (9961.8321 4174.0916) (9958.8397 4172.4733) (9956.3969 4168.0611)
      (9954.8092 4162.0458) (9954.0 4156.0305) (9953.4351 4151.5115) (9952.4122 4149.5115) (9950.2748 4150.2137)
      (9946.687 4153.0076) (9941.8473 4156.6718) (9936.4733 4159.8168) (9931.6336 4161.2061) (9928.3664 4160.229)
      (9927.3893 4156.9771) (9928.7939 4152.1221) (9931.9237 4146.7481) (9935.6031 4141.9084) (9938.3969 4138.3206)
      (9939.0992 4136.1832) (9937.084 4135.1756) (9932.5802 4134.6107) (9926.5496 4133.7863) (9920.5344 4132.1985)
      (9916.1221 4129.771)
    ))
    ; P2779 -- see feature_dimensions_mm.csv
    ("06_ORNAMENT" 1 (
      (9922.6412 2872.4427) (9923.2061 2856.1985) (9925.9847 2840.1069) (9931.1756 2824.3817) (9938.9313 2809.1603)
      (9954.1527 2818.1985) (9967.5115 2829.0534) (9979.0534 2841.4351) (9988.8397 2855.1145) (9996.9008 2869.8473)
      (10003.2824 2885.3588) (10008.0458 2901.4198) (10011.2366 2917.7557) (10012.9008 2934.1221) (10013.084 2950.2748)
      (10011.8473 2965.9542) (10009.2061 2980.9008) (10005.2519 2994.8855) (10000.0 3007.6336) (9988.1374 2998.8855)
      (9976.7176 2988.626) (9965.9237 2977.0229) (9955.9237 2964.2595) (9946.8855 2950.4733) (9939.0229 2935.8626)
      (9932.4885 2920.5954) (9927.4504 2904.8092) (9924.1221 2888.7176)
    ))
    ; P2780 -- see feature_dimensions_mm.csv
    ("06_ORNAMENT" 1 (
      (9943.5115 5069.5115) (9961.8321 5048.9008) (9980.1527 5069.5115) (9961.8321 5090.1221)
    ))
    ; P2781 -- see feature_dimensions_mm.csv
    ("06_ORNAMENT" 1 (
      (9943.5115 4779.4351) (9961.8321 4758.8244) (9980.1527 4779.4351) (9961.8321 4800.0458)
    ))
    ; P2782 -- see feature_dimensions_mm.csv
    ("06_ORNAMENT" 1 (
      (9943.5115 4199.2824) (9961.8321 4178.6718) (9980.1527 4199.2824) (9961.8321 4219.8931)
    ))
    ; P2783 -- see feature_dimensions_mm.csv
    ("06_ORNAMENT" 1 (
      (9943.5115 3909.2061) (9961.8321 3888.5954) (9980.1527 3909.2061) (9961.8321 3929.8168)
    ))
    ; P2784 -- see feature_dimensions_mm.csv
    ("06_ORNAMENT" 1 (
      (9949.9237 5287.0687) (9950.8244 5282.5191) (9953.4046 5278.6565) (9957.2824 5276.0763) (9961.8321 5275.1603)
      (9966.3817 5276.0763) (9970.2595 5278.6565) (9972.8397 5282.5191) (9973.7405 5287.0687) (9972.8397 5291.6336)
      (9970.2595 5295.4962) (9966.3817 5298.0763) (9961.8321 5298.9771) (9957.2824 5298.0763) (9953.4046 5295.4962)
      (9950.8244 5291.6336)
    ))
    ; P2785 -- see feature_dimensions_mm.csv
    ("06_ORNAMENT" 1 (
      (9949.9237 4996.9924) (9950.8244 4992.4427) (9953.4046 4988.5802) (9957.2824 4986.0) (9961.8321 4985.084)
      (9966.3817 4986.0) (9970.2595 4988.5802) (9972.8397 4992.4427) (9973.7405 4996.9924) (9972.8397 5001.5573)
      (9970.2595 5005.4198) (9966.3817 5008.0) (9961.8321 5008.9008) (9957.2824 5008.0) (9953.4046 5005.4198)
      (9950.8244 5001.5573)
    ))
    ; P2786 -- see feature_dimensions_mm.csv
    ("06_ORNAMENT" 1 (
      (9949.9237 4706.916) (9950.8244 4702.3664) (9953.4046 4698.5038) (9957.2824 4695.9237) (9961.8321 4695.0076)
      (9966.3817 4695.9237) (9970.2595 4698.5038) (9972.8397 4702.3664) (9973.7405 4706.916) (9972.8397 4711.4809)
      (9970.2595 4715.3435) (9966.3817 4717.9237) (9961.8321 4718.8244) (9957.2824 4717.9237) (9953.4046 4715.3435)
      (9950.8244 4711.4809)
    ))
    ; P2787 -- see feature_dimensions_mm.csv
    ("06_ORNAMENT" 1 (
      (9949.9237 4126.7634) (9950.8244 4122.2137) (9953.4046 4118.3511) (9957.2824 4115.771) (9961.8321 4114.855)
      (9966.3817 4115.771) (9970.2595 4118.3511) (9972.8397 4122.2137) (9973.7405 4126.7634) (9972.8397 4131.3282)
      (9970.2595 4135.1908) (9966.3817 4137.771) (9961.8321 4138.6718) (9957.2824 4137.771) (9953.4046 4135.1908)
      (9950.8244 4131.3282)
    ))
    ; P2788 -- see feature_dimensions_mm.csv
    ("06_ORNAMENT" 1 (
      (9949.9237 3836.687) (9950.8244 3832.1374) (9950.8855 3832.0611) (9972.7786 3832.0611) (9972.8397 3832.1374)
      (9973.7405 3836.687) (9972.8397 3841.2519) (9970.2595 3845.1145) (9966.3817 3847.6947) (9961.8321 3848.5954)
      (9957.2824 3847.6947) (9953.4046 3845.1145) (9950.8244 3841.2519)
    ))
    ; P2789 -- see feature_dimensions_mm.csv
    ("06_ORNAMENT" 1 (
      (9954.1985 2717.5573) (9956.0611 2711.6794) (9961.3588 2706.4427) (9969.2672 2702.3359) (9978.5496 2699.542)
      (9987.8473 2697.8779) (9995.8473 2696.8702) (10001.5725 2695.7557) (10004.5496 2693.7405) (10004.8092 2690.1679)
      (10002.9008 2684.6412) (9999.7863 2677.2061) (9996.5802 2668.3359) (9994.3511 2658.8855) (9993.9542 2649.9847)
      (9995.8321 2642.7786) (10000.0 2638.229) (10006.0305 2636.9008) (10013.2061 2638.8702) (10020.7176 2643.6641)
      (10027.7863 2650.3053) (10033.8626 2657.5267) (10038.7481 2663.9542) (10042.5802 2668.3511) (10045.8015 2669.9237)
      (10049.0229 2668.3511) (10052.855 2663.9542) (10057.7405 2657.5267) (10063.8168 2650.3053) (10070.8855 2643.6641)
      (10078.3969 2638.8702) (10085.5725 2636.9008) (10091.6031 2638.229) (10095.771 2642.7786) (10097.6489 2649.9847)
      (10097.2519 2658.8855) (10095.0229 2668.3359) (10091.8168 2677.2061) (10088.7023 2684.6412) (10086.7939 2690.1679)
      (10087.0534 2693.7405) (10090.0305 2695.7557) (10095.7557 2696.8702) (10103.7557 2697.8779) (10113.0534 2699.542)
      (10122.3359 2702.3359) (10130.2443 2706.4427) (10135.542 2711.6794) (10137.4046 2717.5573) (10135.542 2723.4351)
      (10130.2443 2728.6718) (10122.3359 2732.7786) (10113.0534 2735.5725) (10103.7557 2737.2366) (10095.7557 2738.2443)
      (10090.0305 2739.3588) (10087.0534 2741.374) (10086.7939 2744.9466) (10088.7023 2750.4733) (10091.8168 2757.9084)
      (10095.0229 2766.7786) (10097.2519 2776.229) (10097.6489 2785.1298) (10095.771 2792.3359) (10091.6031 2796.8855)
      (10085.5725 2798.2137) (10078.3969 2796.2443) (10070.8855 2791.4504) (10063.8168 2784.8092) (10057.7405 2777.5878)
      (10052.855 2771.1603) (10049.0229 2766.7634) (10045.8015 2765.1908) (10042.5802 2766.7634) (10038.7481 2771.1603)
      (10033.8626 2777.5878) (10027.7863 2784.8092) (10020.7176 2791.4504) (10013.2061 2796.2443) (10006.0305 2798.2137)
      (10000.0 2796.8855) (9995.8321 2792.3359) (9993.9542 2785.1298) (9994.3511 2776.229) (9996.5802 2766.7786)
      (9999.7863 2757.9084) (10002.9008 2750.4733) (10004.8092 2744.9466) (10004.5496 2741.374) (10001.5725 2739.3588)
      (9995.8473 2738.2443) (9987.8473 2737.2366) (9978.5496 2735.5725) (9969.2672 2732.7786) (9961.3588 2728.6718)
      (9956.0611 2723.4351)
    ))
    ; P2790 -- see feature_dimensions_mm.csv
    ("06_ORNAMENT" 1 (
      (10016.0305 4344.3206) (10030.5344 4328.0153) (10030.5344 4360.6412)
    ))
    ; P2791 -- see feature_dimensions_mm.csv
    ("06_ORNAMENT" 1 (
      (10016.0305 4054.2443) (10030.5344 4037.9389) (10030.5344 4070.5649)
    ))
    ; P2792 -- see feature_dimensions_mm.csv
    ("06_ORNAMENT" 1 (
      (10019.8473 2717.5573) (10021.1145 2709.542) (10024.8092 2702.3053) (10030.5496 2696.5649) (10037.7863 2692.8702)
      (10045.8015 2691.6031) (10053.8168 2692.8702) (10061.0534 2696.5649) (10066.7939 2702.3053) (10070.4885 2709.542)
      (10071.7557 2717.5573) (10070.4885 2725.5725) (10066.7939 2732.8092) (10061.0534 2738.5496) (10053.8168 2742.2443)
      (10045.8015 2743.5115) (10037.7863 2742.2443) (10030.5496 2738.5496) (10024.8092 2732.8092) (10021.1145 2725.5725)
    ))
    ; P2793 -- see feature_dimensions_mm.csv
    ("06_ORNAMENT" 1 (
      (10027.5115 2910.0916) (10028.8855 2900.9313) (10032.2748 2891.2061) (10037.8779 2880.9618) (10045.8015 2870.229)
      (10059.3282 2870.7023) (10071.0534 2872.7176) (10081.0229 2876.1374) (10089.2977 2880.7939) (10095.9389 2886.5344)
      (10101.0076 2893.2214) (10104.5496 2900.687) (10106.6412 2908.7634) (10107.313 2917.3282) (10106.6412 2926.2137)
      (10104.6718 2935.2519) (10101.4656 2944.3053) (10097.0992 2953.2214) (10091.6031 2961.8321) (10081.145 2960.5191)
      (10071.1756 2958.2443) (10061.8473 2955.0534) (10053.3282 2950.9618) (10045.7405 2946.0305) (10039.2672 2940.2901)
      (10034.0458 2933.7863) (10030.2595 2926.5496) (10028.0153 2918.6412)
    ))
    ; P2794 -- see feature_dimensions_mm.csv
    ("06_ORNAMENT" 1 (
      (10549.6183 7374.0458) (10610.687 7343.5115) (10671.7557 7374.0458) (10610.687 7404.5802)
    ))
    ; P2795 -- see feature_dimensions_mm.csv
    ("06_ORNAMENT" 1 (
      (10549.6183 7282.4427) (10610.687 7251.9084) (10671.7557 7282.4427) (10610.687 7312.9771)
    ))
    ; P2796 -- see feature_dimensions_mm.csv
    ("06_ORNAMENT" 1 (
      (10549.6183 7190.8397) (10610.687 7160.3053) (10671.7557 7190.8397) (10610.687 7221.374)
    ))
    ; P2797 -- see feature_dimensions_mm.csv
    ("06_ORNAMENT" 1 (
      (10701.9237 4928.0) (10703.2214 4908.3511) (10706.1985 4887.9389) (10710.7786 4867.0534) (10716.9618 4846.0305)
      (10724.7176 4825.1908) (10734.0 4804.8244) (10744.7939 4785.2672) (10757.084 4766.8092) (10770.8092 4749.7863)
      (10785.9695 4734.5191) (10802.5191 4721.2977) (10820.4427 4710.458) (10839.6947 4702.2901) (10859.5115 4711.4504)
      (10877.9542 4723.2214) (10894.9618 4737.2519) (10910.5038 4753.2061) (10924.5344 4770.7786) (10937.0382 4789.6183)
      (10939.4504 4793.9695) (10939.4809 4793.8931) (10949.1908 4781.2519) (10961.8321 4771.542) (10976.5649 4765.4351)
      (10992.3664 4763.3588) (11008.1679 4765.4351) (11022.9008 4771.542) (11035.542 4781.2519) (11045.2519 4793.8931)
      (11051.3588 4808.626) (11053.4351 4824.4275) (11051.3588 4840.229) (11045.2519 4854.9618) (11035.542 4867.6031)
      (11022.9008 4877.313) (11008.1679 4883.4198) (10992.3664 4885.4962) (10976.5649 4883.4198) (10973.1756 4882.0153)
      (10975.1298 4891.374) (10977.4351 4909.542) (10979.7863 4912.1679) (10998.3053 4935.8015) (11015.3893 4960.5344)
      (11030.9313 4985.9237) (11044.7634 5011.5878) (11056.7634 5037.1298) (11066.8244 5062.1221) (11074.7939 5086.1527)
      (11080.5496 5108.8397) (11083.9695 5129.771) (11064.229 5117.6183) (11043.8931 5103.0229) (11023.2672 5086.2137)
      (11019.7557 5083.0076) (11020.9771 5085.8779) (11027.2061 5104.5649) (11028.9924 5112.0916) (11035.542 5117.1298)
      (11045.2519 5129.771) (11051.3588 5144.5038) (11053.4351 5160.3053) (11051.3588 5176.1069) (11045.2519 5190.8397)
      (11041.5573 5195.6641) (11050.3206 5202.6565) (11066.7176 5217.9389) (11081.7099 5234.1069) (11083.9695 5236.9466)
      (11083.9695 5308.9618) (11072.3817 5305.4198) (11052.4427 5297.6947) (11032.6107 5288.3664) (11013.1908 5277.5267)
      (10994.4885 5265.2366) (10991.3588 5262.8244) (10998.3053 5271.6794) (11015.3893 5296.4122) (11030.9313 5321.8015)
      (11043.4962 5345.1298) (11055.0382 5344.8855) (11076.9771 5347.0992) (11083.9695 5348.5802) (11083.9695 5374.0458)
      (11084.2443 5378.9924) (11087.6489 5410.4275) (11088.4122 5415.1603) (11089.6794 5419.7863) (11095.7405 5438.2595)
      (11079.6183 5428.4885) (11075.7099 5425.6031) (11080.5496 5444.7176) (11083.9695 5465.6489) (11064.229 5453.4962)
      (11060.2137 5450.626) (11062.9924 5468.9924) (11064.5496 5491.542) (11064.3817 5513.9542) (11062.5954 5535.9389)
      (11059.2824 5557.1603) (11054.5802 5577.313) (11048.5649 5596.0763) (11041.3588 5613.1298) (11033.0687 5628.1832)
      (11022.4427 5612.9466) (11012.626 5595.8779) (11003.7405 5577.2672) (10995.9542 5557.3588) (10995.7863 5556.8092)
      (10992.3664 5557.2519) (10976.5649 5555.1756) (10961.8321 5549.0687) (10949.1908 5539.3588) (10939.4809 5526.7176)
      (10933.374 5511.9847) (10931.2977 5496.1832) (10933.374 5480.3817) (10939.4809 5465.6489) (10949.1908 5453.0076)
      (10961.8321 5443.2977) (10976.5649 5437.1908) (10979.8015 5436.7634) (10980.7176 5426.5038) (10984.8397 5405.374)
      (10989.6794 5390.1221) (10982.458 5382.7939) (10962.9313 5360.8092) (10944.4122 5337.5573) (10929.1298 5316.0)
      (10928.8244 5317.4656) (10922.7786 5338.687) (10915.4046 5358.855) (10906.855 5377.6947) (10897.2977 5394.9313)
      (10886.9008 5410.2595) (10875.8321 5423.3893) (10868.3817 5406.3817) (10862.0763 5387.7252) (10856.9924 5367.7252)
      (10853.8779 5350.229) (10853.5725 5350.5344) (10841.6947 5361.0534) (10829.5725 5370.3053) (10817.4351 5378.1985)
      (10805.4656 5384.5802) (10793.8931 5389.313) (10795.542 5375.8626) (10798.5038 5361.7252) (10802.7023 5347.145)
      (10808.0916 5332.3359) (10814.6107 5317.5267) (10822.229 5302.9313) (10830.8855 5288.7939) (10840.5191 5275.3435)
      (10851.0992 5262.7786) (10853.0687 5260.7939) (10853.374 5258.0916) (10857.6641 5236.3511) (10863.8321 5215.374)
      (10871.9847 5195.4656) (10874.0153 5191.7863) (10872.626 5185.4962) (10870.229 5160.3053) (10887.8168 5169.2977)
      (10894.626 5160.0305) (10909.2977 5145.1298) (10931.1145 5146.0153) (10933.1298 5146.3664) (10933.374 5144.5038)
      (10939.4809 5129.771) (10949.1908 5117.1298) (10961.8321 5107.4198) (10964.7328 5106.2137) (10961.8779 5104.4122)
      (10944.2443 5091.4046) (10927.313 5076.9771) (10911.374 5061.2672) (10896.687 5044.4275) (10883.5725 5026.5649)
      (10872.2748 5007.8321) (10868.2443 4999.2672) (10865.0229 5003.0382) (10862.0153 5006.0916) (10861.5878 5013.4504)
      (10858.1374 5035.6641) (10852.7023 5057.6183) (10845.5115 5079.0382) (10836.7786 5099.6947) (10826.7176 5119.313)
      (10815.542 5137.6641) (10803.4809 5154.4733) (10790.7481 5169.5115) (10777.5573 5182.5191) (10764.1374 5193.2366)
      (10760.1527 5175.0992) (10757.6031 5155.5725) (10756.5344 5134.9771) (10756.9618 5113.6031) (10758.916 5091.7863)
      (10762.458 5069.8168) (10767.5878 5048.0305) (10774.3664 5026.7328) (10782.8092 5006.2443) (10792.9618 4986.8855)
      (10804.8397 4968.9313) (10818.5038 4952.7481) (10833.9542 4938.6107) (10850.9771 4927.0382) (10851.0992 4926.9008)
      (10862.5344 4915.4656) (10874.8092 4905.374) (10885.9237 4898.1221) (10878.2901 4875.2672) (10872.626 4849.6183)
      (10872.229 4845.5115) (10861.3282 4826.4733) (10851.9389 4806.3969) (10844.5191 4785.8321) (10839.3435 4764.9466)
      (10839.1298 4763.3893) (10838.5191 4767.6794) (10832.9466 4789.2519) (10825.2214 4810.3664) (10815.6183 4830.8397)
      (10804.3817 4850.4427) (10791.7863 4868.9924) (10778.0763 4886.2748) (10763.542 4902.0763) (10748.4427 4916.229)
      (10733.0076 4928.4885) (10717.542 4938.6718) (10702.2901 4946.5649)
    ))
    ; P2798 -- see feature_dimensions_mm.csv
    ("06_ORNAMENT" 1 (
      (10793.8931 5725.1908) (10795.542 5711.7405) (10798.5038 5697.6031) (10802.7023 5683.0229) (10808.0916 5668.2137)
      (10814.6107 5653.4046) (10822.229 5638.8092) (10830.8855 5624.6718) (10840.5191 5611.2214) (10851.0992 5598.6565)
      (10862.5344 5587.2214) (10874.8092 5577.1298) (10885.9237 5569.8779) (10878.2901 5547.0229) (10872.626 5521.374)
      (10870.229 5496.1832) (10893.9695 5508.3206) (10916.916 5523.5573) (10938.9618 5541.5115) (10959.9542 5561.771)
      (10979.7863 5583.9237) (10998.3053 5607.5573) (11015.3893 5632.2901) (11030.9313 5657.6794) (11044.7634 5683.3435)
      (11056.7634 5708.8855) (11066.8244 5733.8779) (11074.7939 5757.9084) (11080.5496 5780.5954) (11083.9695 5801.5267)
      (11064.229 5789.374) (11043.8931 5774.7786) (11023.2672 5757.9695) (11002.6718 5739.1908) (10998.1985 5734.626)
      (10946.5649 5786.2595) (10870.229 5709.9237) (10928.7786 5651.374) (10927.2214 5649.1908) (10911.6947 5624.1985)
      (10905.3282 5612.1985) (10902.2901 5619.7252) (10894.6718 5634.5191) (10885.771 5648.7023) (10875.8321 5662.1679)
      (10865.0229 5674.7939) (10853.5725 5686.4122) (10841.6947 5696.9313) (10829.5725 5706.1832) (10817.4351 5714.0763)
      (10805.4656 5720.458)
    ))
    ; P2799 -- see feature_dimensions_mm.csv
    ("06_ORNAMENT" 1 (
      (10793.8931 4717.5573) (10795.542 4704.1069) (10798.5038 4689.9695) (10802.7023 4675.3893) (10808.0916 4660.5802)
      (10814.6107 4645.771) (10822.229 4631.1756) (10830.8855 4617.0382) (10840.5191 4603.5878) (10851.0992 4591.0229)
      (10862.5344 4579.5878) (10874.8092 4569.4962) (10885.9237 4562.2443) (10878.2901 4539.3893) (10872.626 4513.7405)
      (10870.229 4488.5496) (10893.9695 4500.687) (10916.916 4515.9237) (10938.9618 4533.8779) (10959.9542 4554.1374)
      (10979.7863 4576.2901) (10998.3053 4599.9237) (11015.3893 4624.6565) (11030.9313 4650.0458) (11044.7634 4675.7099)
      (11056.7634 4701.2519) (11066.8244 4726.2443) (11074.7939 4750.2748) (11080.5496 4772.9618) (11083.9695 4793.8931)
      (11064.229 4781.7405) (11043.8931 4767.145) (11023.2672 4750.3359) (11002.6718 4731.5573) (10982.458 4711.0382)
      (10962.9313 4689.0534) (10944.4122 4665.8015) (10927.2214 4641.5573) (10911.6947 4616.5649) (10905.3282 4604.5649)
      (10902.2901 4612.0916) (10894.6718 4626.8855) (10885.771 4641.0687) (10875.8321 4654.5344) (10865.0229 4667.1603)
      (10853.5725 4678.7786) (10841.6947 4689.2977) (10829.5725 4698.5496) (10817.4351 4706.4427) (10805.4656 4712.8244)
    ))
    ; P2800 -- see feature_dimensions_mm.csv
    ("06_ORNAMENT" 1 (
      (10901.0382 1851.9542) (10901.7252 1851.2824) (10910.6565 1844.0611) (10920.3969 1837.3893) (10930.8244 1831.4046)
      (10941.8321 1826.1985) (10953.2519 1821.9084) (10964.9771 1818.6565) (10976.8855 1816.5496) (10988.8244 1815.6947)
      (11000.6718 1816.2443) (11012.2901 1818.2901) (11023.5573 1821.9695) (11034.3511 1827.3893) (11027.0992 1837.6336)
      (11018.626 1846.6107) (11009.0992 1854.3206) (10998.7023 1860.8244) (10987.6031 1866.1527) (10976.0153 1870.3359)
      (10964.0916 1873.4198) (10952.0305 1875.4198) (10940.0153 1876.3969) (10928.2137 1876.3511) (10916.8092 1875.3588)
      (10906.0 1873.4198) (10901.7405 1872.2137)
    ))
    ; P2801 -- see feature_dimensions_mm.csv
    ("06_ORNAMENT" 1 (
      (10903.2824 4945.5267) (10909.9237 4949.0992) (10905.3282 4940.4427)
    ))
    ; P2802 -- see feature_dimensions_mm.csv
    ("06_ORNAMENT" 1 (
      (10931.2977 5923.6641) (10934.4122 5913.8626) (10943.2366 5905.1298) (10956.4122 5898.2901) (10971.8931 5893.6336)
      (10987.374 5890.8702) (11000.7023 5889.1756) (11010.2595 5887.313) (11015.2214 5883.9695) (11015.6336 5878.0153)
      (11012.4733 5868.8092) (11007.2824 5856.4122) (11001.9237 5841.6183) (10998.2137 5825.8779) (10997.5573 5811.0534)
      (11000.7023 5799.0382) (11007.6336 5791.4504) (11017.6794 5789.2366) (11029.6489 5792.5344) (11042.1679 5800.5191)
      (11053.9389 5811.5878) (11064.0611 5823.6183) (11072.2137 5834.3206) (11078.5954 5841.6641) (11083.9695 5844.2748)
      (11089.3435 5841.6641) (11095.7252 5834.3206) (11103.8779 5823.6183) (11114.0 5811.5878) (11125.771 5800.5191)
      (11138.2901 5792.5344) (11150.2595 5789.2366) (11160.3053 5791.4504) (11167.2366 5799.0382) (11170.3817 5811.0534)
      (11169.7252 5825.8779) (11166.0153 5841.6183) (11160.6565 5856.4122) (11155.4656 5868.8092) (11152.3053 5878.0153)
      (11152.7176 5883.9695) (11157.6794 5887.313) (11167.2366 5889.1756) (11180.5649 5890.8702) (11196.0458 5893.6336)
      (11211.5267 5898.2901) (11224.7023 5905.1298) (11233.5267 5913.8626) (11236.6412 5923.6641) (11233.5267 5933.4656)
      (11224.7023 5942.1985) (11211.5267 5949.0382) (11196.0458 5953.6947) (11180.5649 5956.458) (11167.2366 5958.1527)
      (11157.6794 5960.0153) (11152.7176 5963.3588) (11152.3053 5969.313) (11155.4656 5978.5191) (11160.6565 5990.916)
      (11166.0153 6005.7099) (11169.7252 6021.4351) (11170.3817 6036.2748) (11167.2366 6048.2901) (11160.3053 6055.8779)
      (11150.2595 6058.0916) (11138.2901 6054.7939) (11125.771 6046.8092) (11114.0 6035.7405) (11103.8779 6023.7099)
      (11095.7252 6013.0076) (11089.3435 6005.6641) (11083.9695 6003.0534) (11078.5954 6005.6641) (11072.2137 6013.0076)
      (11064.0611 6023.7099) (11053.9389 6035.7405) (11042.1679 6046.8092) (11029.6489 6054.7939) (11017.6794 6058.0916)
      (11007.6336 6055.8779) (11000.7023 6048.2901) (10997.5573 6036.2748) (10998.2137 6021.4351) (11001.9237 6005.7099)
      (11007.2824 5990.916) (11012.4733 5978.5191) (11015.6336 5969.313) (11015.2214 5963.3588) (11010.2595 5960.0153)
      (11000.7023 5958.1527) (10987.374 5956.458) (10971.8931 5953.6947) (10956.4122 5949.0382) (10943.2366 5942.1985)
      (10934.4122 5933.4656)
    ))
    ; P2803 -- see feature_dimensions_mm.csv
    ("06_ORNAMENT" 1 (
      (10931.2977 4488.5496) (10933.374 4472.7481) (10939.4809 4458.0153) (10949.1908 4445.374) (10961.8321 4435.6641)
      (10976.5649 4429.5573) (10992.3664 4427.4809) (11008.1679 4429.5573) (11022.9008 4435.6641) (11035.542 4445.374)
      (11045.2519 4458.0153) (11051.3588 4472.7481) (11053.4351 4488.5496) (11051.3588 4504.3511) (11045.2519 4519.084)
      (11035.542 4531.7252) (11022.9008 4541.4351) (11008.1679 4547.542) (10992.3664 4549.6183) (10976.5649 4547.542)
      (10961.8321 4541.4351) (10949.1908 4531.7252) (10939.4809 4519.084) (10933.374 4504.3511)
    ))
    ; P2804 -- see feature_dimensions_mm.csv
    ("06_ORNAMENT" 1 (
      (10977.0992 1740.458) (10991.9084 1731.4656) (11008.3664 1723.374) (11026.1985 1716.2901) (11045.1298 1710.3511)
      (11064.9008 1705.6641) (11085.2519 1702.3511) (11105.8931 1700.5496) (11126.5954 1700.3817) (11147.0534 1701.9695)
      (11167.0229 1705.4198) (11186.2443 1710.8702) (11204.4275 1718.4427) (11221.313 1728.2748) (11236.6412 1740.458)
      (11220.2443 1752.6412) (11202.3817 1762.4733) (11183.3282 1770.0458) (11163.3893 1775.4962) (11142.8397 1778.9466)
      (11121.9542 1780.5344) (11101.0382 1780.3664) (11080.3359 1778.5649) (11060.1679 1775.2519) (11040.8092 1770.5649)
      (11022.5344 1764.626) (11005.6489 1757.542) (10990.3969 1749.4504)
    ))
    ; P2805 -- see feature_dimensions_mm.csv
    ("06_ORNAMENT" 1 (
      (11013.3282 2085.9084) (11015.2977 2075.5725) (11018.3664 2064.9618) (11022.4885 2054.2443) (11027.5878 2043.6031)
      (11033.6336 2033.1908) (11040.5649 2023.1908) (11048.3053 2013.7557) (11056.8397 2005.0687) (11066.0916 1997.2977)
      (11076.0 1990.5954) (11086.5344 1985.145) (11097.6336 1981.1145) (11109.2214 1978.6565) (11121.2824 1977.9542)
      (11120.1374 1990.458) (11117.2672 2002.458) (11112.8855 2013.9084) (11107.1298 2024.7481) (11100.1832 2034.9008)
      (11092.2443 2044.3206) (11083.4504 2052.9466) (11074.0153 2060.7176) (11064.0763 2067.5573) (11053.8473 2073.4351)
      (11043.4809 2078.2595) (11033.145 2082.0) (11023.0382 2084.5649)
    ))
    ; P2806 -- see feature_dimensions_mm.csv
    ("06_ORNAMENT" 1 (
      (11013.3282 1395.0076) (11023.6641 1396.9771) (11034.2748 1400.0458) (11044.9924 1404.1679) (11055.6336 1409.2672)
      (11064.8702 1414.6412) (11064.9313 1413.1603) (11066.4122 1406.8702) (11068.5649 1400.9466) (11070.6412 1395.9847)
      (11071.9084 1392.3053) (11071.7405 1389.9237) (11069.7557 1388.5802) (11065.9389 1387.8473) (11060.5954 1387.1603)
      (11054.4122 1386.0611) (11048.2137 1384.1985) (11042.9466 1381.4504) (11039.4046 1377.9695) (11038.1679 1374.0458)
      (11039.4046 1370.1221) (11042.9466 1366.6412) (11048.2137 1363.8931) (11054.4122 1362.0305) (11060.5954 1360.9313)
      (11065.9389 1360.2443) (11069.7557 1359.5115) (11071.7405 1358.1679) (11071.9084 1355.7863) (11070.6412 1352.1069)
      (11068.5649 1347.145) (11066.4122 1341.2214) (11064.9313 1334.9313) (11064.6718 1329.0076) (11065.9237 1324.1985)
      (11068.7023 1321.1603) (11072.7176 1320.2748) (11077.5115 1321.5878) (11082.5191 1324.7786) (11087.2214 1329.2214)
      (11091.2824 1334.0305) (11094.5344 1338.3053) (11097.084 1341.2519) (11099.2366 1342.2901) (11101.3893 1341.2519)
      (11103.9389 1338.3053) (11107.1908 1334.0305) (11111.2519 1329.2214) (11115.9542 1324.7786) (11120.9618 1321.5878)
      (11125.7557 1320.2748) (11129.771 1321.1603) (11132.5496 1324.1985) (11133.8015 1329.0076) (11133.542 1334.9313)
      (11132.0611 1341.2214) (11129.9084 1347.145) (11127.8321 1352.1069) (11126.5649 1355.7863) (11126.7328 1358.1679)
      (11128.7176 1359.5115) (11132.5344 1360.2443) (11137.8779 1360.9313) (11144.0611 1362.0305) (11150.2595 1363.8931)
      (11155.5267 1366.6412) (11159.0687 1370.1221) (11160.3053 1374.0458) (11159.0687 1377.9695) (11155.5267 1381.4504)
      (11150.2595 1384.1985) (11144.0611 1386.0611) (11137.8779 1387.1603) (11132.5344 1387.8473) (11128.7176 1388.5802)
      (11126.7328 1389.9237) (11126.5649 1392.3053) (11127.8321 1395.9847) (11129.9084 1400.9466) (11132.0611 1406.8702)
      (11133.542 1413.1603) (11133.8015 1419.084) (11132.5496 1423.8931) (11129.771 1426.9313) (11125.7557 1427.8168)
      (11120.9618 1426.5038) (11115.9542 1423.313) (11111.2519 1418.8702) (11107.1908 1414.0611) (11103.9389 1409.7863)
      (11101.3893 1406.8397) (11099.2366 1405.8015) (11097.084 1406.8397) (11094.5344 1409.7863) (11091.2824 1414.0611)
      (11087.2214 1418.8702) (11082.5191 1423.313) (11079.6031 1425.1603) (11085.4809 1429.9847) (11094.1679 1438.5191)
      (11101.9389 1447.771) (11108.6412 1457.6794) (11114.0916 1468.2137) (11118.1221 1479.313) (11120.5802 1490.9008)
      (11121.2824 1502.9618) (11108.7786 1501.8168) (11096.7786 1498.9466) (11085.3282 1494.5649) (11074.4885 1488.8092)
      (11064.3359 1481.8626) (11054.916 1473.9237) (11046.2901 1465.1298) (11038.5191 1455.6947) (11031.6794 1445.7557)
      (11025.8015 1435.5267) (11020.9771 1425.1603) (11017.2366 1414.8244) (11014.6718 1404.7176)
    ))
    ; P2807 -- see feature_dimensions_mm.csv
    ("06_ORNAMENT" 1 (
      (11028.229 1931.2977) (11036.5649 1916.1069) (11046.7786 1900.8702) (11058.6718 1885.8168) (11072.0916 1871.2061)
      (11086.8702 1857.2672) (11102.8397 1844.229) (11119.8321 1832.3359) (11137.6641 1821.8473) (11156.1679 1812.9771)
      (11175.1908 1805.9847) (11194.5649 1801.1145) (11214.0916 1798.5802) (11233.6336 1798.6412) (11253.0076 1801.5267)
      (11244.9008 1820.2748) (11234.3359 1837.7252) (11221.6336 1853.8015) (11207.084 1868.4885) (11191.0229 1881.771)
      (11173.7252 1893.5725) (11155.5115 1903.8931) (11136.7023 1912.6718) (11117.5725 1919.8931) (11098.4733 1925.5115)
      (11079.6641 1929.5115) (11061.4962 1931.8168) (11044.2443 1932.4275)
    ))
    ; P2808 -- see feature_dimensions_mm.csv
    ("06_ORNAMENT" 1 (
      (11028.229 1549.6183) (11045.5573 1549.2366) (11063.8473 1550.458) (11082.8397 1553.2366) (11102.1985 1557.5573)
      (11121.6641 1563.374) (11140.9466 1570.687) (11159.7252 1579.4656) (11177.7405 1589.6641) (11194.6718 1601.2519)
      (11210.229 1614.2443) (11224.1527 1628.5649) (11236.1069 1644.2137) (11245.8168 1661.1756) (11253.0076 1679.3893)
      (11232.7023 1681.7405) (11212.3206 1681.313) (11192.0458 1678.3511) (11172.0458 1673.1145) (11152.5191 1665.8321)
      (11133.6489 1656.7481) (11115.6031 1646.1374) (11098.5954 1634.2443) (11082.7786 1621.2977) (11068.3511 1607.5573)
      (11055.5115 1593.2672) (11044.4122 1578.687) (11035.2672 1564.0458)
    ))
    ; P2809 -- see feature_dimensions_mm.csv
    ("06_ORNAMENT" 1 (
      (11038.1679 7374.0458) (11099.2366 7343.5115) (11160.3053 7374.0458) (11099.2366 7404.5802)
    ))
    ; P2810 -- see feature_dimensions_mm.csv
    ("06_ORNAMENT" 1 (
      (11038.1679 7282.4427) (11099.2366 7251.9084) (11160.3053 7282.4427) (11099.2366 7312.9771)
    ))
    ; P2811 -- see feature_dimensions_mm.csv
    ("06_ORNAMENT" 1 (
      (11038.1679 7190.8397) (11099.2366 7160.3053) (11160.3053 7190.8397) (11099.2366 7221.374)
    ))
    ; P2812 -- see feature_dimensions_mm.csv
    ("06_ORNAMENT" 1 (
      (11038.1679 5923.6641) (11040.4122 5909.5115) (11046.916 5896.7481) (11057.0534 5886.6107) (11069.8168 5880.1069)
      (11083.9695 5877.8626) (11098.1221 5880.1069) (11110.8855 5886.6107) (11121.0229 5896.7481) (11127.5267 5909.5115)
      (11129.771 5923.6641) (11127.5267 5937.8168) (11121.0229 5950.5802) (11110.8855 5960.7176) (11098.1221 5967.2214)
      (11083.9695 5969.4656) (11069.8168 5967.2214) (11057.0534 5960.7176) (11046.916 5950.5802) (11040.4122 5937.8168)
    ))
    ; P2813 -- see feature_dimensions_mm.csv
    ("06_ORNAMENT" 1 (
      (11038.1679 2137.4046) (11039.4046 2133.4809) (11042.9466 2130.0) (11048.2137 2127.2519) (11054.4122 2125.3893)
      (11060.5954 2124.2901) (11065.9389 2123.6031) (11069.7557 2122.8702) (11071.7405 2121.5267) (11071.9084 2119.145)
      (11070.6412 2115.4656) (11068.5649 2110.5038) (11066.4122 2104.5802) (11064.9313 2098.2901) (11064.6718 2092.3664)
      (11065.9237 2087.5573) (11068.7023 2084.5191) (11072.7176 2083.6336) (11077.5115 2084.9466) (11082.5191 2088.1374)
      (11087.2214 2092.5802) (11091.2824 2097.3893) (11094.5344 2101.6641) (11097.084 2104.6107) (11099.2366 2105.6489)
      (11101.3893 2104.6107) (11103.9389 2101.6641) (11107.1908 2097.3893) (11111.2519 2092.5802) (11115.9542 2088.1374)
      (11120.9618 2084.9466) (11125.7557 2083.6336) (11129.771 2084.5191) (11132.5496 2087.5573) (11133.8015 2092.3664)
      (11133.542 2098.2901) (11132.0611 2104.5802) (11129.9084 2110.5038) (11127.8321 2115.4656) (11126.5649 2119.145)
      (11126.7328 2121.5267) (11128.7176 2122.8702) (11132.5344 2123.6031) (11137.8779 2124.2901) (11144.0611 2125.3893)
      (11150.2595 2127.2519) (11155.5267 2130.0) (11159.0687 2133.4809) (11160.3053 2137.4046) (11159.0687 2141.3282)
      (11155.5267 2144.8092) (11150.2595 2147.5573) (11144.0611 2149.4198) (11137.8779 2150.5191) (11132.5344 2151.2061)
      (11128.7176 2151.9389) (11126.7328 2153.2824) (11126.5649 2155.6641) (11127.8321 2159.3435) (11129.9084 2164.3053)
      (11132.0611 2170.229) (11133.542 2176.5191) (11133.8015 2182.4427) (11132.5496 2187.2519) (11129.771 2190.2901)
      (11125.7557 2191.1756) (11120.9618 2189.8626) (11115.9542 2186.6718) (11111.2519 2182.229) (11107.1908 2177.4198)
      (11103.9389 2173.145) (11101.3893 2170.1985) (11099.2366 2169.1603) (11097.084 2170.1985) (11094.5344 2173.145)
      (11091.2824 2177.4198) (11087.2214 2182.229) (11082.5191 2186.6718) (11081.8321 2187.0992) (11079.9542 2185.8473)
      (11065.3893 2174.5954) (11066.4122 2170.229) (11068.5649 2164.3053) (11070.6412 2159.3435) (11071.9084 2155.6641)
      (11071.7405 2153.2824) (11069.7557 2151.9389) (11065.9389 2151.2061) (11060.5954 2150.5191) (11054.4122 2149.4198)
      (11048.2137 2147.5573) (11042.9466 2144.8092) (11039.4046 2141.3282)
    ))
    ; P2814 -- see feature_dimensions_mm.csv
    ("06_ORNAMENT" 1 (
      (11068.7023 3007.6336) (11099.2366 2977.0992) (11129.771 3007.6336) (11099.2366 3038.1679)
    ))
    ; P2815 -- see feature_dimensions_mm.csv
    ("06_ORNAMENT" 1 (
      (11068.7023 2916.0305) (11099.2366 2885.4962) (11129.771 2916.0305) (11099.2366 2946.5649)
    ))
    ; P2816 -- see feature_dimensions_mm.csv
    ("06_ORNAMENT" 1 (
      (11139.0382 5590.626) (11141.4046 5569.5725) (11146.3969 5549.2214) (11153.9847 5530.4733) (11175.0076 5551.3893)
      (11178.5038 5554.5344) (11209.8168 5579.8473) (11212.8702 5582.1221) (11220.3511 5587.2061) (11216.7328 5585.4962)
      (11198.2901 5574.3969) (11197.0534 5573.4351) (11199.6489 5576.9008) (11210.9618 5596.0916) (11220.4275 5616.4885)
      (11228.1069 5637.7557) (11234.0305 5659.5725) (11238.2443 5681.6031) (11240.7634 5703.4962) (11241.6794 5724.9618)
      (11240.9924 5745.6489) (11238.7481 5765.2214) (11235.0229 5783.3588) (11229.8168 5799.7252) (11216.4275 5786.8702)
      (11203.4656 5772.0458) (11191.1145 5755.5115) (11179.6031 5737.5115) (11169.0992 5718.2748) (11159.8473 5698.0458)
      (11152.0153 5677.084) (11145.8168 5655.6183) (11141.4504 5633.8779) (11139.1298 5612.1374)
    ))
    ; P2817 -- see feature_dimensions_mm.csv
    ("06_ORNAMENT" 1 (
      (11166.8092 1425.9237) (11167.9389 1409.9084) (11183.1298 1418.2443) (11198.3664 1428.458) (11213.4198 1440.3511)
      (11228.0305 1453.771) (11241.9695 1468.5496) (11255.0076 1484.5191) (11266.9008 1501.4962) (11277.3893 1519.3435)
      (11286.2595 1537.8473) (11293.2519 1556.8702) (11298.1221 1576.2443) (11300.6565 1595.771) (11300.5954 1615.313)
      (11297.7099 1634.687) (11278.9618 1626.5802) (11261.5115 1616.0153) (11245.4351 1603.313) (11230.7481 1588.7634)
      (11217.4656 1572.7023) (11205.6641 1555.4046) (11195.3435 1537.1908) (11186.5649 1518.3817) (11179.3435 1499.2519)
      (11173.7252 1480.1527) (11169.7252 1461.3435) (11167.4198 1443.1756)
    ))
    ; P2818 -- see feature_dimensions_mm.csv
    ("06_ORNAMENT" 1 (
      (11167.5573 2053.6794) (11168.7786 2035.3893) (11171.5573 2016.3969) (11175.8779 1997.0382) (11181.6947 1977.5725)
      (11189.0076 1958.2901) (11197.7863 1939.5115) (11207.9847 1921.4962) (11219.5725 1904.5649) (11232.5649 1889.0076)
      (11246.8855 1875.084) (11262.5344 1863.1298) (11279.4962 1853.4198) (11297.7099 1846.229) (11300.0611 1866.5344)
      (11299.6336 1886.916) (11296.6718 1907.1908) (11291.4351 1927.1908) (11284.1527 1946.7176) (11275.0687 1965.5878)
      (11264.458 1983.6336) (11252.5649 2000.6412) (11239.6183 2016.458) (11225.8779 2030.8855) (11211.5878 2043.7252)
      (11197.0076 2054.8244) (11182.3664 2063.9695) (11167.9389 2071.0076)
    ))
    ; P2819 -- see feature_dimensions_mm.csv
    ("06_ORNAMENT" 1 (
      (11222.8397 1321.6947) (11222.8855 1309.8931) (11223.8779 1298.4885) (11225.8168 1287.6794) (11228.6412 1277.6489)
      (11232.3359 1268.5496) (11240.3053 1275.4351) (11247.9542 1283.4046) (11255.1756 1292.3359) (11261.8473 1302.0763)
      (11267.8321 1312.5038) (11273.0382 1323.5115) (11277.3282 1334.9313) (11280.5802 1346.6565) (11282.687 1358.5649)
      (11283.542 1370.5038) (11282.9924 1382.3511) (11280.9466 1393.9695) (11277.2672 1405.2366) (11271.8473 1416.0305)
      (11261.6031 1408.7786) (11252.626 1400.3053) (11244.916 1390.7786) (11238.4122 1380.3817) (11233.084 1369.2824)
      (11228.9008 1357.6947) (11225.8168 1345.771) (11223.8168 1333.7099)
    ))
    ; P2820 -- see feature_dimensions_mm.csv
    ("06_ORNAMENT" 1 (
      (11223.542 2168.5802) (11223.5573 2156.5496) (11224.5649 2144.4122) (11226.5649 2132.3817) (11229.6031 2120.5954)
      (11233.7252 2109.2366) (11238.9618 2098.4733) (11245.3588 2088.4885) (11252.9466 2079.4504) (11261.7557 2071.5267)
      (11271.8473 2064.8855) (11277.0992 2076.2901) (11280.626 2088.1069) (11282.5496 2100.229) (11282.9771 2112.4885)
      (11282.0458 2124.7481) (11279.8779 2136.8855) (11276.5802 2148.7481) (11272.2901 2160.1985) (11267.1145 2171.084)
      (11261.1908 2181.2977) (11254.626 2190.6565) (11247.542 2199.0534) (11240.0763 2206.3359) (11232.3359 2212.3664)
      (11228.8702 2202.4122) (11226.229 2191.6794) (11224.4427 2180.3511)
    ))
    ; P2821 -- see feature_dimensions_mm.csv
    ("06_ORNAMENT" 1 (
      (11251.9084 1740.458) (11253.9695 1719.6031) (11260.0458 1699.5573) (11269.9237 1681.084) (11283.2061 1664.8855)
      (11299.4046 1651.6031) (11317.8779 1641.7252) (11337.9237 1635.6336) (11358.7786 1633.5878) (11379.6336 1635.6336)
      (11399.6794 1641.7252) (11418.1527 1651.6031) (11434.3511 1664.8855) (11447.6336 1681.084) (11457.5115 1699.5573)
      (11463.6031 1719.6031) (11465.6489 1740.458) (11463.6031 1761.313) (11457.5115 1781.3588) (11447.6336 1799.8321)
      (11434.3511 1816.0305) (11418.1527 1829.313) (11399.6794 1839.1908) (11379.6336 1845.2672) (11358.7786 1847.3282)
      (11337.9237 1845.2672) (11317.8779 1839.1908) (11299.4046 1829.313) (11283.2061 1816.0305) (11269.9237 1799.8321)
      (11260.0458 1781.3588) (11253.9695 1761.313)
    ))
    ; P2822 -- see feature_dimensions_mm.csv
    ("06_ORNAMENT" 1 (
      (11282.4427 1740.458) (11283.9084 1725.5725) (11288.2595 1711.2519) (11295.313 1698.0458) (11304.7939 1686.4733)
      (11316.3664 1676.9924) (11329.5725 1669.9389) (11343.8931 1665.5878) (11358.7786 1664.1221) (11373.6641 1665.5878)
      (11387.9847 1669.9389) (11401.1908 1676.9924) (11412.7634 1686.4733) (11422.2443 1698.0458) (11429.2977 1711.2519)
      (11433.6489 1725.5725) (11435.1145 1740.458) (11433.6489 1755.3435) (11429.2977 1769.6641) (11422.2443 1782.8702)
      (11412.7634 1794.4427) (11401.1908 1803.9237) (11387.9847 1810.9771) (11373.6641 1815.3282) (11358.7786 1816.7939)
      (11343.8931 1815.3282) (11329.5725 1810.9771) (11316.3664 1803.9237) (11304.7939 1794.4427) (11295.313 1782.8702)
      (11288.2595 1769.6641) (11283.9084 1755.3435)
    ))
    ; P2823 -- see feature_dimensions_mm.csv
    ("06_ORNAMENT" 1 (
      (11318.7023 1972.6412) (11320.2901 1952.1832) (11323.7405 1932.2137) (11329.1908 1912.9924) (11336.7634 1894.8092)
      (11346.5954 1877.9237) (11358.7786 1862.5954) (11370.9618 1878.9924) (11380.7939 1896.855) (11388.3664 1915.9084)
      (11393.8168 1935.8473) (11397.2672 1956.3969) (11398.855 1977.2824) (11398.687 1998.1985) (11396.8855 2018.9008)
      (11393.5725 2039.0687) (11388.8855 2058.4275) (11382.9466 2076.7023) (11375.8626 2093.5878) (11367.771 2108.8397)
      (11358.7786 2122.1374) (11349.7863 2107.3282) (11341.6947 2090.8702) (11334.6107 2073.0382) (11328.6718 2054.1069)
      (11323.9847 2034.3359) (11320.6718 2013.9847) (11318.8702 1993.3435)
    ))
    ; P2824 -- see feature_dimensions_mm.csv
    ("06_ORNAMENT" 1 (
      (11318.7023 1503.6336) (11318.8702 1482.7023) (11320.6718 1462.0153) (11323.9847 1441.8473) (11328.6718 1422.4885)
      (11334.6107 1404.2137) (11341.6947 1387.313) (11349.7863 1372.0763) (11358.7786 1358.7786) (11367.771 1373.5878)
      (11375.8626 1390.0458) (11382.9466 1407.8779) (11388.8855 1426.8092) (11393.5725 1446.5802) (11396.8855 1466.916)
      (11398.687 1487.5725) (11398.855 1508.2748) (11397.2672 1528.7328) (11393.8168 1548.7023) (11388.3664 1567.9237)
      (11380.7939 1586.1069) (11370.9618 1602.9924) (11358.7786 1618.3206) (11346.5954 1601.9237) (11336.7634 1584.0611)
      (11329.1908 1565.0076) (11323.7405 1545.0687) (11320.2901 1524.5191)
    ))
    ; P2825 -- see feature_dimensions_mm.csv
    ("06_ORNAMENT" 1 (
      (11326.8855 5722.9618) (11327.8168 5702.0458) (11331.7405 5681.4962) (11350.3664 5670.1069) (11360.6718 5665.5878)
      (11381.8931 5675.2366) (11383.5573 5675.9542) (11431.0229 5695.3282) (11432.458 5695.8931) (11481.7557 5714.1069)
      (11483.0229 5714.5496) (11528.5344 5729.8779) (11513.8473 5732.0916) (11491.6794 5733.8626) (11469.2977 5734.0305)
      (11447.0076 5732.5038) (11425.0992 5729.1603) (11403.8779 5723.8931) (11383.6183 5716.5954) (11382.229 5715.9084)
      (11385.4351 5718.7939) (11400.2901 5735.4198) (11413.5573 5753.5725) (11425.2366 5772.9313) (11435.2977 5793.1756)
      (11443.7099 5813.9542) (11450.4733 5834.9466) (11455.542 5855.8168) (11458.916 5876.229) (11459.313 5881.084)
      (11462.5649 5881.9847) (11473.8321 5889.1603) (11484.4275 5899.1298) (11493.542 5909.9542) (11500.8702 5919.5878)
      (11506.6107 5926.1985) (11511.4504 5928.5496) (11516.2901 5926.1985) (11522.0305 5919.5878) (11529.3588 5909.9542)
      (11538.4733 5899.1298) (11549.0687 5889.1603) (11557.145 5884.0153) (11554.7786 5879.6794) (11546.458 5859.8321)
      (11540.5802 5839.4809) (11537.4198 5818.7786) (11537.2519 5797.8626) (11553.2977 5783.0534) (11571.2214 5770.5344)
      (11590.7023 5760.1832) (11606.9008 5753.7252) (11639.2977 5762.9313) (11640.1832 5763.1756) (11692.0916 5776.7939)
      (11692.9008 5777.0076) (11744.3053 5789.4962) (11745.0382 5789.6794) (11767.9084 5794.8397) (11765.9084 5795.8931)
      (11746.3511 5804.5191) (11725.7405 5811.9542) (11704.3359 5818.0153) (11682.4275 5822.5649) (11660.2595 5825.4046)
      (11638.1221 5826.3969) (11616.2748 5825.374) (11594.9924 5822.1679) (11593.4809 5821.771) (11597.2061 5823.9695)
      (11615.0076 5837.374) (11631.5573 5852.5954) (11646.7939 5869.313) (11660.6107 5887.1908) (11672.916 5905.9237)
      (11683.6489 5925.1908) (11692.687 5944.6718) (11699.9695 5964.0458) (11705.4046 5982.9924) (11708.8855 6001.1756)
      (11710.3511 6018.2901) (11693.0534 6011.5267) (11675.4046 6002.8092) (11657.6794 5992.2443) (11640.1374 5980.0153)
      (11623.084 5966.2595) (11606.7939 5951.1298) (11591.5267 5934.7481) (11585.0992 5926.687) (11580.4733 5939.4656)
      (11575.8015 5950.626) (11572.9466 5958.916) (11573.3282 5964.2748) (11577.7863 5967.2824) (11586.3817 5968.9618)
      (11598.3817 5970.4885) (11612.3206 5972.9771) (11626.2443 5977.1603) (11638.1069 5983.3282) (11646.0611 5991.1756)
      (11648.855 6000.0) (11646.0611 6008.8244) (11638.1069 6016.6718) (11626.2443 6022.8397) (11612.3206 6027.0229)
      (11598.3817 6029.5115) (11586.3817 6031.0382) (11577.7863 6032.7176) (11573.3282 6035.7252) (11572.9466 6041.084)
      (11575.8015 6049.374) (11580.4733 6060.5344) (11585.2977 6073.8473) (11588.626 6088.0) (11589.2214 6101.3435)
      (11586.3969 6112.1679) (11580.1527 6118.9924) (11571.1145 6120.9771) (11560.3359 6118.0153) (11549.0687 6110.8397)
      (11538.4733 6100.8702) (11529.3588 6090.0458) (11522.0305 6080.4122) (11516.2901 6073.8015) (11511.4504 6071.4504)
      (11506.6107 6073.8015) (11500.8702 6080.4122) (11493.542 6090.0458) (11484.4275 6100.8702) (11473.8321 6110.8397)
      (11462.5649 6118.0153) (11451.7863 6120.9771) (11442.7481 6118.9924) (11436.5038 6112.1679) (11433.6794 6101.3435)
      (11434.2748 6088.0) (11437.6031 6073.8473) (11442.4275 6060.5344) (11447.0992 6049.374) (11449.9542 6041.084)
      (11449.5725 6035.7252) (11445.1145 6032.7176) (11436.5191 6031.0382) (11424.5191 6029.5115) (11410.5802 6027.0229)
      (11396.6565 6022.8397) (11384.7939 6016.6718) (11376.8397 6008.8244) (11374.0458 6000.0) (11376.8397 5991.1756)
      (11384.7939 5983.3282) (11396.6565 5977.1603) (11410.5802 5972.9771) (11424.5191 5970.4885) (11436.5191 5968.9618)
      (11445.1145 5967.2824) (11449.5725 5964.2748) (11449.9542 5958.916) (11447.0992 5950.626) (11442.4275 5939.4656)
      (11437.6031 5926.1527) (11435.0992 5915.4809) (11427.2519 5909.4504) (11411.9237 5895.6336) (11397.1145 5880.229)
      (11383.0687 5863.4046) (11370.0458 5845.374) (11358.2748 5826.3359) (11348.0 5806.4885) (11339.4809 5786.0305)
      (11332.9618 5765.1603) (11328.687 5744.0763)
    ))
    ; P2826 -- see feature_dimensions_mm.csv
    ("06_ORNAMENT" 1 (
      (11343.5115 3007.6336) (11374.0458 2977.0992) (11404.5802 3007.6336) (11374.0458 3038.1679)
    ))
    ; P2827 -- see feature_dimensions_mm.csv
    ("06_ORNAMENT" 1 (
      (11343.5115 2916.0305) (11374.0458 2885.4962) (11404.5802 2916.0305) (11374.0458 2946.5649)
    ))
    ; P2828 -- see feature_dimensions_mm.csv
    ("06_ORNAMENT" 1 (
      (11371.7557 5175.8321) (11373.4504 5172.687) (11378.0763 5170.1374) (11384.3817 5168.4733) (11390.7023 5167.6031)
      (11395.4351 5167.0229) (11397.542 5165.9542) (11396.8092 5163.7099) (11393.8779 5159.9542) (11390.0153 5154.8855)
      (11386.7328 5149.2519) (11385.2672 5144.1679) (11386.2901 5140.7481) (11389.7099 5139.7252) (11394.7939 5141.1908)
      (11400.4275 5144.4733) (11405.4962 5148.3206) (11409.2519 5151.2519) (11411.4962 5151.9847) (11412.5649 5149.8931)
      (11413.1603 5145.1603) (11414.0153 5138.8397) (11415.6794 5132.5344) (11418.229 5127.9084) (11421.374 5126.2137)
      (11424.5191 5127.9084) (11427.0687 5132.5344) (11428.7328 5138.8397) (11429.5878 5145.1603) (11430.1832 5149.8931)
      (11431.2519 5151.9847) (11433.4962 5151.2519) (11437.2519 5148.3206) (11442.3206 5144.4733) (11447.9542 5141.1908)
      (11453.0382 5139.7252) (11456.458 5140.7481) (11457.4809 5144.1679) (11456.0153 5149.2519) (11452.7328 5154.8855)
      (11448.8702 5159.9542) (11445.9389 5163.7099) (11445.2061 5165.9542) (11447.313 5167.0229) (11452.0458 5167.6031)
      (11458.3664 5168.4733) (11464.6718 5170.1374) (11469.2977 5172.687) (11470.9924 5175.8321) (11469.2977 5178.9771)
      (11464.6718 5181.5267) (11458.3664 5183.1908) (11452.0458 5184.0458) (11447.313 5184.6412) (11445.2061 5185.7099)
      (11445.9389 5187.9542) (11448.8702 5191.7099) (11452.7328 5196.7786) (11456.0153 5202.4122) (11457.4809 5207.4962)
      (11456.458 5210.916) (11453.0382 5211.9389) (11447.9542 5210.4733) (11442.3206 5207.1908) (11437.2519 5203.3282)
      (11433.4962 5200.3969) (11431.2519 5199.6641) (11430.1832 5201.771) (11429.5878 5206.5038) (11428.7328 5212.8092)
      (11427.0687 5219.1145) (11424.5191 5223.7557) (11421.374 5225.4504) (11418.229 5223.7557) (11415.6794 5219.1145)
      (11414.0153 5212.8092) (11413.1603 5206.5038) (11412.5649 5201.771) (11411.4962 5199.6641) (11409.2519 5200.3969)
      (11405.4962 5203.3282) (11400.4275 5207.1908) (11394.7939 5210.4733) (11389.7099 5211.9389) (11386.2901 5210.916)
      (11385.2672 5207.4962) (11386.7328 5202.4122) (11390.0153 5196.7786) (11393.8779 5191.7099) (11396.8092 5187.9542)
      (11397.542 5185.7099) (11395.4351 5184.6412) (11390.7023 5184.0458) (11384.3817 5183.1908) (11378.0763 5181.5267)
      (11373.4504 5178.9771)
    ))
    ; P2829 -- see feature_dimensions_mm.csv
    ("06_ORNAMENT" 1 (
      (11371.7557 4864.3817) (11373.4504 4861.2366) (11378.0763 4858.687) (11384.3817 4857.0229) (11390.7023 4856.1527)
      (11395.4351 4855.5725) (11397.542 4854.5038) (11396.8092 4852.2595) (11393.8779 4848.5038) (11390.0153 4843.4351)
      (11386.7328 4837.8015) (11385.2672 4832.7176) (11386.2901 4829.2977) (11389.7099 4828.2748) (11394.7939 4829.7405)
      (11400.4275 4833.0229) (11405.4962 4836.8702) (11409.2519 4839.8015) (11411.4962 4840.5344) (11412.5649 4838.4427)
      (11413.1603 4833.7099) (11414.0153 4827.3893) (11415.6794 4821.084) (11418.229 4816.458) (11421.374 4814.7634)
      (11424.5191 4816.458) (11427.0687 4821.084) (11428.7328 4827.3893) (11429.5878 4833.7099) (11430.1832 4838.4427)
      (11431.2519 4840.5344) (11433.4962 4839.8015) (11437.2519 4836.8702) (11442.3206 4833.0229) (11447.9542 4829.7405)
      (11453.0382 4828.2748) (11456.458 4829.2977) (11457.4809 4832.7176) (11456.0153 4837.8015) (11452.7328 4843.4351)
      (11448.8702 4848.5038) (11445.9389 4852.2595) (11445.2061 4854.5038) (11447.313 4855.5725) (11452.0458 4856.1527)
      (11458.3664 4857.0229) (11464.6718 4858.687) (11469.2977 4861.2366) (11470.9924 4864.3817) (11469.2977 4867.5267)
      (11464.6718 4870.0763) (11458.3664 4871.7405) (11452.0458 4872.5954) (11447.313 4873.1908) (11445.2061 4874.2595)
      (11445.9389 4876.5038) (11448.8702 4880.2595) (11452.7328 4885.3282) (11456.0153 4890.9618) (11457.4809 4896.0458)
      (11456.458 4899.4656) (11453.0382 4900.4885) (11447.9542 4899.0229) (11442.3206 4895.7405) (11437.2519 4891.8779)
      (11433.4962 4888.9466) (11431.2519 4888.2137) (11430.1832 4890.3206) (11429.5878 4895.0534) (11428.7328 4901.3588)
      (11427.0687 4907.6641) (11424.5191 4912.3053) (11421.374 4914.0) (11418.229 4912.3053) (11415.6794 4907.6641)
      (11414.0153 4901.3588) (11413.1603 4895.0534) (11412.5649 4890.3206) (11411.4962 4888.2137) (11409.2519 4888.9466)
      (11405.4962 4891.8779) (11400.4275 4895.7405) (11394.7939 4899.0229) (11389.7099 4900.4885) (11386.2901 4899.4656)
      (11385.2672 4896.0458) (11386.7328 4890.9618) (11390.0153 4885.3282) (11393.8779 4880.2595) (11396.8092 4876.5038)
      (11397.542 4874.2595) (11395.4351 4873.1908) (11390.7023 4872.5954) (11384.3817 4871.7405) (11378.0763 4870.0763)
      (11373.4504 4867.5267)
    ))
    ; P2830 -- see feature_dimensions_mm.csv
    ("06_ORNAMENT" 1 (
      (11371.7557 4552.9313) (11373.4504 4549.7863) (11378.0763 4547.2366) (11384.3817 4545.5725) (11390.7023 4544.7023)
      (11395.4351 4544.1221) (11397.542 4543.0534) (11396.8092 4540.8092) (11393.8779 4537.0534) (11390.0153 4531.9847)
      (11386.7328 4526.3511) (11385.2672 4521.2672) (11386.2901 4517.8473) (11389.7099 4516.8244) (11394.7939 4518.2901)
      (11400.4275 4521.5725) (11405.4962 4525.4198) (11409.2519 4528.3511) (11411.4962 4529.084) (11412.5649 4526.9924)
      (11413.1603 4522.2595) (11414.0153 4515.9389) (11415.6794 4509.6336) (11418.229 4505.0076) (11421.374 4503.313)
      (11424.5191 4505.0076) (11427.0687 4509.6336) (11428.7328 4515.9389) (11429.5878 4522.2595) (11430.1832 4526.9924)
      (11431.2519 4529.084) (11433.4962 4528.3511) (11437.2519 4525.4198) (11442.3206 4521.5725) (11447.9542 4518.2901)
      (11453.0382 4516.8244) (11456.458 4517.8473) (11457.4809 4521.2672) (11456.0153 4526.3511) (11452.7328 4531.9847)
      (11448.8702 4537.0534) (11445.9389 4540.8092) (11445.2061 4543.0534) (11447.313 4544.1221) (11452.0458 4544.7023)
      (11458.3664 4545.5725) (11464.6718 4547.2366) (11469.2977 4549.7863) (11470.9924 4552.9313) (11469.2977 4556.0763)
      (11464.6718 4558.626) (11458.3664 4560.2901) (11452.0458 4561.145) (11447.313 4561.7405) (11445.2061 4562.8092)
      (11445.9389 4565.0534) (11448.8702 4568.8092) (11452.7328 4573.8779) (11456.0153 4579.5115) (11457.4809 4584.5954)
      (11456.458 4588.0153) (11453.0382 4589.0382) (11447.9542 4587.5725) (11442.3206 4584.2901) (11437.2519 4580.4275)
      (11433.4962 4577.4962) (11431.2519 4576.7634) (11430.1832 4578.8702) (11429.5878 4583.6031) (11428.7328 4589.9084)
      (11427.0687 4596.2137) (11424.5191 4600.855) (11421.374 4602.5496) (11418.229 4600.855) (11415.6794 4596.2137)
      (11414.0153 4589.9084) (11413.1603 4583.6031) (11412.5649 4578.8702) (11411.4962 4576.7634) (11409.2519 4577.4962)
      (11405.4962 4580.4275) (11400.4275 4584.2901) (11394.7939 4587.5725) (11389.7099 4589.0382) (11386.2901 4588.0153)
      (11385.2672 4584.5954) (11386.7328 4579.5115) (11390.0153 4573.8779) (11393.8779 4568.8092) (11396.8092 4565.0534)
      (11397.542 4562.8092) (11395.4351 4561.7405) (11390.7023 4561.145) (11384.3817 4560.2901) (11378.0763 4558.626)
      (11373.4504 4556.0763)
    ))
    ; P2831 -- see feature_dimensions_mm.csv
    ("06_ORNAMENT" 1 (
      (11371.7557 4241.4809) (11373.4504 4238.3359) (11378.0763 4235.7863) (11384.3817 4234.1221) (11390.7023 4233.2519)
      (11395.4351 4232.6718) (11397.542 4231.6031) (11396.8092 4229.3588) (11393.8779 4225.6031) (11390.0153 4220.5344)
      (11386.7328 4214.9008) (11385.2672 4209.8168) (11386.2901 4206.3969) (11389.7099 4205.374) (11394.7939 4206.8397)
      (11400.4275 4210.1221) (11405.4962 4213.9695) (11409.2519 4216.9008) (11411.4962 4217.6336) (11412.5649 4215.542)
      (11413.1603 4210.8092) (11414.0153 4204.4885) (11415.6794 4198.1832) (11418.229 4193.5573) (11421.374 4191.8626)
      (11424.5191 4193.5573) (11427.0687 4198.1832) (11428.7328 4204.4885) (11429.5878 4210.8092) (11430.1832 4215.542)
      (11431.2519 4217.6336) (11433.4962 4216.9008) (11437.2519 4213.9695) (11442.3206 4210.1221) (11447.9542 4206.8397)
      (11453.0382 4205.374) (11456.458 4206.3969) (11457.4809 4209.8168) (11456.0153 4214.9008) (11452.7328 4220.5344)
      (11448.8702 4225.6031) (11445.9389 4229.3588) (11445.2061 4231.6031) (11447.313 4232.6718) (11452.0458 4233.2519)
      (11458.3664 4234.1221) (11464.6718 4235.7863) (11469.2977 4238.3359) (11470.9924 4241.4809) (11469.2977 4244.626)
      (11464.6718 4247.1756) (11458.3664 4248.8397) (11452.0458 4249.6947) (11447.313 4250.2901) (11445.2061 4251.3588)
      (11445.9389 4253.6031) (11448.8702 4257.3588) (11452.7328 4262.4275) (11456.0153 4268.0611) (11457.4809 4273.145)
      (11456.458 4276.5649) (11453.0382 4277.5878) (11447.9542 4276.1221) (11442.3206 4272.8397) (11437.2519 4268.9771)
      (11433.4962 4266.0458) (11431.2519 4265.313) (11430.1832 4267.4198) (11429.5878 4272.1527) (11428.7328 4278.458)
      (11427.0687 4284.7634) (11424.5191 4289.4046) (11421.374 4291.0992) (11418.229 4289.4046) (11415.6794 4284.7634)
      (11414.0153 4278.458) (11413.1603 4272.1527) (11412.5649 4267.4198) (11411.4962 4265.313) (11409.2519 4266.0458)
      (11405.4962 4268.9771) (11400.4275 4272.8397) (11394.7939 4276.1221) (11389.7099 4277.5878) (11386.2901 4276.5649)
      (11385.2672 4273.145) (11386.7328 4268.0611) (11390.0153 4262.4275) (11393.8779 4257.3588) (11396.8092 4253.6031)
      (11397.542 4251.3588) (11395.4351 4250.2901) (11390.7023 4249.6947) (11384.3817 4248.8397) (11378.0763 4247.1756)
      (11373.4504 4244.626)
    ))
    ; P2832 -- see feature_dimensions_mm.csv
    ("06_ORNAMENT" 1 (
      (11371.7557 3930.0305) (11373.4504 3926.8855) (11378.0763 3924.3359) (11384.3817 3922.6718) (11390.7023 3921.8015)
      (11395.4351 3921.2214) (11397.542 3920.1527) (11396.8092 3917.9084) (11393.8779 3914.1527) (11390.0153 3909.084)
      (11386.7328 3903.4504) (11385.2672 3898.3664) (11386.2901 3894.9466) (11389.7099 3893.9237) (11394.7939 3895.3893)
      (11400.4275 3898.6718) (11405.4962 3902.5191) (11409.2519 3905.4504) (11411.4962 3906.1832) (11412.5649 3904.0916)
      (11413.1603 3899.3588) (11414.0153 3893.0382) (11415.6794 3886.7328) (11418.229 3882.1069) (11421.374 3880.4122)
      (11424.5191 3882.1069) (11427.0687 3886.7328) (11428.7328 3893.0382) (11429.5878 3899.3588) (11430.1832 3904.0916)
      (11431.2519 3906.1832) (11433.4962 3905.4504) (11437.2519 3902.5191) (11442.3206 3898.6718) (11447.9542 3895.3893)
      (11453.0382 3893.9237) (11456.458 3894.9466) (11457.4809 3898.3664) (11456.0153 3903.4504) (11452.7328 3909.084)
      (11448.8702 3914.1527) (11445.9389 3917.9084) (11445.2061 3920.1527) (11447.313 3921.2214) (11452.0458 3921.8015)
      (11458.3664 3922.6718) (11464.6718 3924.3359) (11469.2977 3926.8855) (11470.9924 3930.0305) (11469.2977 3933.1756)
      (11464.6718 3935.7252) (11458.3664 3937.3893) (11452.0458 3938.2443) (11447.313 3938.8397) (11445.2061 3939.9084)
      (11445.9389 3942.1527) (11448.8702 3945.9084) (11452.7328 3950.9771) (11456.0153 3956.6107) (11457.4809 3961.6947)
      (11456.458 3965.1145) (11453.0382 3966.1374) (11447.9542 3964.6718) (11442.3206 3961.3893) (11437.2519 3957.5267)
      (11433.4962 3954.5954) (11431.2519 3953.8626) (11430.1832 3955.9695) (11429.5878 3960.7023) (11428.7328 3967.0076)
      (11427.0687 3973.313) (11424.5191 3977.9542) (11421.374 3979.6489) (11418.229 3977.9542) (11415.6794 3973.313)
      (11414.0153 3967.0076) (11413.1603 3960.7023) (11412.5649 3955.9695) (11411.4962 3953.8626) (11409.2519 3954.5954)
      (11405.4962 3957.5267) (11400.4275 3961.3893) (11394.7939 3964.6718) (11389.7099 3966.1374) (11386.2901 3965.1145)
      (11385.2672 3961.6947) (11386.7328 3956.6107) (11390.0153 3950.9771) (11393.8779 3945.9084) (11396.8092 3942.1527)
      (11397.542 3939.9084) (11395.4351 3938.8397) (11390.7023 3938.2443) (11384.3817 3937.3893) (11378.0763 3935.7252)
      (11373.4504 3933.1756)
    ))
    ; P2833 -- see feature_dimensions_mm.csv
    ("06_ORNAMENT" 1 (
      (11409.4656 5175.8321) (11410.3664 5171.2672) (11412.9466 5167.4046) (11416.8244 5164.8244) (11421.374 5163.9237)
      (11425.9237 5164.8244) (11429.8015 5167.4046) (11432.3817 5171.2672) (11433.2824 5175.8321) (11432.3817 5180.3817)
      (11429.8015 5184.2443) (11425.9237 5186.8244) (11421.374 5187.7405) (11416.8244 5186.8244) (11412.9466 5184.2443)
      (11410.3664 5180.3817)
    ))
    ; P2834 -- see feature_dimensions_mm.csv
    ("06_ORNAMENT" 1 (
      (11409.4656 4864.3817) (11410.3664 4859.8168) (11412.9466 4855.9542) (11416.8244 4853.374) (11421.374 4852.4733)
      (11425.9237 4853.374) (11429.8015 4855.9542) (11432.3817 4859.8168) (11433.2824 4864.3817) (11432.3817 4868.9313)
      (11429.8015 4872.7939) (11425.9237 4875.374) (11421.374 4876.2901) (11416.8244 4875.374) (11412.9466 4872.7939)
      (11410.3664 4868.9313)
    ))
    ; P2835 -- see feature_dimensions_mm.csv
    ("06_ORNAMENT" 1 (
      (11409.4656 4552.9313) (11410.3664 4548.3664) (11412.9466 4544.5038) (11416.8244 4541.9237) (11421.374 4541.0229)
      (11425.9237 4541.9237) (11429.8015 4544.5038) (11432.3817 4548.3664) (11433.2824 4552.9313) (11432.3817 4557.4809)
      (11429.8015 4561.3435) (11425.9237 4563.9237) (11421.374 4564.8397) (11416.8244 4563.9237) (11412.9466 4561.3435)
      (11410.3664 4557.4809)
    ))
    ; P2836 -- see feature_dimensions_mm.csv
    ("06_ORNAMENT" 1 (
      (11409.4656 4241.4809) (11410.3664 4236.916) (11412.9466 4233.0534) (11416.8244 4230.4733) (11421.374 4229.5725)
      (11425.9237 4230.4733) (11429.8015 4233.0534) (11432.3817 4236.916) (11433.2824 4241.4809) (11432.3817 4246.0305)
      (11429.8015 4249.8931) (11425.9237 4252.4733) (11421.374 4253.3893) (11416.8244 4252.4733) (11412.9466 4249.8931)
      (11410.3664 4246.0305)
    ))
    ; P2837 -- see feature_dimensions_mm.csv
    ("06_ORNAMENT" 1 (
      (11409.4656 3930.0305) (11410.3664 3925.4656) (11412.9466 3921.6031) (11416.8244 3919.0229) (11421.374 3918.1221)
      (11425.9237 3919.0229) (11429.8015 3921.6031) (11432.3817 3925.4656) (11433.2824 3930.0305) (11432.3817 3934.5802)
      (11429.8015 3938.4427) (11425.9237 3941.0229) (11421.374 3941.9389) (11416.8244 3941.0229) (11412.9466 3938.4427)
      (11410.3664 3934.5802)
    ))
    ; P2838 -- see feature_dimensions_mm.csv
    ("06_ORNAMENT" 1 (
      (11416.9008 1885.145) (11416.9618 1865.6031) (11419.8473 1846.229) (11438.5954 1854.3359) (11456.0458 1864.9008)
      (11472.1221 1877.6031) (11486.8092 1892.1527) (11500.0916 1908.2137) (11511.8931 1925.5115) (11522.2137 1943.7252)
      (11530.9924 1962.5344) (11538.2137 1981.6641) (11543.8321 2000.7634) (11547.8321 2019.5725) (11550.1374 2037.7405)
      (11550.7481 2054.9924) (11549.6183 2071.0076) (11534.4275 2062.6718) (11519.1908 2052.458) (11504.1527 2040.5649)
      (11489.5267 2027.145) (11475.5878 2012.3664) (11462.5496 1996.3969) (11450.6565 1979.4046) (11440.1679 1961.5725)
      (11431.2977 1943.0687) (11424.3053 1924.0458) (11419.4351 1904.6718)
    ))
    ; P2839 -- see feature_dimensions_mm.csv
    ("06_ORNAMENT" 1 (
      (11417.4962 1614.3817) (11417.9237 1594.0) (11420.8855 1573.7252) (11426.1221 1553.7252) (11433.4046 1534.1985)
      (11442.4885 1515.3282) (11453.0992 1497.2824) (11464.9924 1480.2748) (11477.9389 1464.458) (11491.6794 1450.0305)
      (11505.9695 1437.1908) (11520.5496 1426.0916) (11535.1908 1416.9466) (11549.6183 1409.9084) (11550.0 1427.2366)
      (11548.7786 1445.5267) (11546.0 1464.5191) (11541.6794 1483.8779) (11535.8626 1503.3435) (11528.5496 1522.626)
      (11519.771 1541.4046) (11509.5725 1559.4198) (11497.9847 1576.3511) (11484.9924 1591.9084) (11470.6718 1605.8321)
      (11455.0229 1617.7863) (11438.0611 1627.4962) (11419.8473 1634.687)
    ))
    ; P2840 -- see feature_dimensions_mm.csv
    ("06_ORNAMENT" 1 (
      (11434.0153 2110.4122) (11434.5649 2098.5649) (11436.6107 2086.9466) (11440.2901 2075.6794) (11445.7099 2064.8855)
      (11455.9542 2072.1374) (11464.9313 2080.6107) (11472.6412 2090.1374) (11479.145 2100.5344) (11484.4733 2111.6336)
      (11488.6565 2123.2214) (11491.7405 2135.145) (11493.7405 2147.2061) (11494.7176 2159.2214) (11494.6718 2171.0229)
      (11493.6794 2182.4275) (11491.7405 2193.2366) (11488.916 2203.2672) (11485.2214 2212.3664) (11477.2519 2205.4809)
      (11469.6031 2197.5115) (11462.3817 2188.5802) (11455.7099 2178.8397) (11449.7252 2168.4122) (11444.5191 2157.4046)
      (11440.229 2145.9847) (11436.9771 2134.2595) (11434.8702 2122.3511)
    ))
    ; P2841 -- see feature_dimensions_mm.csv
    ("06_ORNAMENT" 1 (
      (11434.5802 1368.4275) (11435.5115 1356.1679) (11437.6794 1344.0305) (11440.9771 1332.1679) (11445.2672 1320.7176)
      (11450.4427 1309.8321) (11456.3664 1299.6183) (11462.9313 1290.2595) (11470.0153 1281.8626) (11477.4809 1274.5802)
      (11485.2214 1268.5496) (11488.687 1278.5038) (11491.3282 1289.2366) (11493.1145 1300.5649) (11494.0153 1312.3359)
      (11494.0 1324.3664) (11492.9924 1336.5038) (11490.9924 1348.5344) (11487.9542 1360.3206) (11483.8321 1371.6794)
      (11478.5954 1382.4427) (11472.1985 1392.4275) (11464.6107 1401.4656) (11455.8015 1409.3893) (11445.7099 1416.0305)
      (11440.458 1404.626) (11436.9313 1392.8092) (11435.0076 1380.687)
    ))
    ; P2842 -- see feature_dimensions_mm.csv
    ("06_ORNAMENT" 1 (
      (11449.6183 5331.5573) (11451.313 5328.4122) (11455.9389 5325.8626) (11462.2443 5324.1985) (11468.5649 5323.3282)
      (11473.2977 5322.7481) (11475.4046 5321.6794) (11474.6718 5319.4351) (11471.7405 5315.6794) (11467.8779 5310.6107)
      (11464.5954 5304.9771) (11463.1298 5299.8931) (11464.1527 5296.4733) (11467.5725 5295.4504) (11472.6565 5296.916)
      (11478.2901 5300.1985) (11483.3588 5304.0458) (11487.1145 5306.9771) (11489.3588 5307.7099) (11490.4275 5305.6183)
      (11491.0229 5300.8855) (11491.8779 5294.5649) (11493.542 5288.2595) (11496.0916 5283.6336) (11499.2366 5281.9389)
      (11502.3817 5283.6336) (11504.9313 5288.2595) (11506.5954 5294.5649) (11507.4504 5300.8855) (11508.0458 5305.6183)
      (11509.1145 5307.7099) (11511.3588 5306.9771) (11515.1145 5304.0458) (11520.1832 5300.1985) (11525.8168 5296.916)
      (11530.9008 5295.4504) (11534.3206 5296.4733) (11535.3435 5299.8931) (11533.8779 5304.9771) (11530.5954 5310.6107)
      (11526.7328 5315.6794) (11523.8015 5319.4351) (11523.0687 5321.6794) (11525.1756 5322.7481) (11529.9084 5323.3282)
      (11536.229 5324.1985) (11542.5344 5325.8626) (11547.1603 5328.4122) (11548.855 5331.5573) (11547.1603 5334.7023)
      (11542.5344 5337.2519) (11536.229 5338.916) (11529.9084 5339.771) (11525.1756 5340.3664) (11523.0687 5341.4351)
      (11523.8015 5343.6794) (11526.7328 5347.4351) (11530.5954 5352.5038) (11533.8779 5358.1374) (11535.3435 5363.2214)
      (11534.3206 5366.6412) (11530.9008 5367.6641) (11525.8168 5366.1985) (11520.1832 5362.916) (11515.1145 5359.0534)
      (11511.3588 5356.1221) (11509.1145 5355.3893) (11508.0458 5357.4962) (11507.4504 5362.229) (11506.5954 5368.5344)
      (11504.9313 5374.8397) (11502.3817 5379.4809) (11499.2366 5381.1756) (11496.0916 5379.4809) (11493.542 5374.8397)
      (11491.8779 5368.5344) (11491.0229 5362.229) (11490.4275 5357.4962) (11489.3588 5355.3893) (11487.1145 5356.1221)
      (11483.3588 5359.0534) (11478.2901 5362.916) (11472.6565 5366.1985) (11467.5725 5367.6641) (11464.1527 5366.6412)
      (11463.1298 5363.2214) (11464.5954 5358.1374) (11467.8779 5352.5038) (11471.7405 5347.4351) (11474.6718 5343.6794)
      (11475.4046 5341.4351) (11473.2977 5340.3664) (11468.5649 5339.771) (11462.2443 5338.916) (11455.9389 5337.2519)
      (11451.313 5334.7023)
    ))
    ; P2843 -- see feature_dimensions_mm.csv
    ("06_ORNAMENT" 1 (
      (11449.6183 5020.1069) (11451.313 5016.9618) (11455.9389 5014.4122) (11462.2443 5012.7481) (11468.5649 5011.8779)
      (11473.2977 5011.2977) (11475.4046 5010.229) (11474.6718 5007.9847) (11471.7405 5004.229) (11467.8779 4999.1603)
      (11464.5954 4993.5267) (11463.1298 4988.4427) (11464.1527 4985.0229) (11467.5725 4984.0) (11472.6565 4985.4656)
      (11478.2901 4988.7481) (11483.3588 4992.5954) (11487.1145 4995.5267) (11489.3588 4996.2595) (11490.4275 4994.1679)
      (11491.0229 4989.4351) (11491.8779 4983.1145) (11493.542 4976.8092) (11496.0916 4972.1832) (11499.2366 4970.4885)
      (11502.3817 4972.1832) (11504.9313 4976.8092) (11506.5954 4983.1145) (11507.4504 4989.4351) (11508.0458 4994.1679)
      (11509.1145 4996.2595) (11511.3588 4995.5267) (11515.1145 4992.5954) (11520.1832 4988.7481) (11525.8168 4985.4656)
      (11530.9008 4984.0) (11534.3206 4985.0229) (11535.3435 4988.4427) (11533.8779 4993.5267) (11530.5954 4999.1603)
      (11526.7328 5004.229) (11523.8015 5007.9847) (11523.0687 5010.229) (11525.1756 5011.2977) (11529.9084 5011.8779)
      (11536.229 5012.7481) (11542.5344 5014.4122) (11547.1603 5016.9618) (11548.855 5020.1069) (11547.1603 5023.2519)
      (11542.5344 5025.8015) (11536.229 5027.4656) (11529.9084 5028.3206) (11525.1756 5028.916) (11523.0687 5029.9847)
      (11523.8015 5032.229) (11526.7328 5035.9847) (11530.5954 5041.0534) (11533.8779 5046.687) (11535.3435 5051.771)
      (11534.3206 5055.1908) (11530.9008 5056.2137) (11525.8168 5054.7481) (11520.1832 5051.4656) (11515.1145 5047.6031)
      (11511.3588 5044.6718) (11509.1145 5043.9389) (11508.0458 5046.0458) (11507.4504 5050.7786) (11506.5954 5057.084)
      (11504.9313 5063.3893) (11502.3817 5068.0305) (11499.2366 5069.7252) (11496.0916 5068.0305) (11493.542 5063.3893)
      (11491.8779 5057.084) (11491.0229 5050.7786) (11490.4275 5046.0458) (11489.3588 5043.9389) (11487.1145 5044.6718)
      (11483.3588 5047.6031) (11478.2901 5051.4656) (11472.6565 5054.7481) (11467.5725 5056.2137) (11464.1527 5055.1908)
      (11463.1298 5051.771) (11464.5954 5046.687) (11467.8779 5041.0534) (11471.7405 5035.9847) (11474.6718 5032.229)
      (11475.4046 5029.9847) (11473.2977 5028.916) (11468.5649 5028.3206) (11462.2443 5027.4656) (11455.9389 5025.8015)
      (11451.313 5023.2519)
    ))
    ; P2844 -- see feature_dimensions_mm.csv
    ("06_ORNAMENT" 1 (
      (11449.6183 4708.6565) (11451.313 4705.5115) (11455.9389 4702.9618) (11462.2443 4701.2977) (11468.5649 4700.4275)
      (11473.2977 4699.8473) (11475.4046 4698.7786) (11474.6718 4696.5344) (11471.7405 4692.7786) (11467.8779 4687.7099)
      (11464.5954 4682.0763) (11463.1298 4676.9924) (11464.1527 4673.5725) (11467.5725 4672.5496) (11472.6565 4674.0153)
      (11478.2901 4677.2977) (11483.3588 4681.145) (11487.1145 4684.0763) (11489.3588 4684.8092) (11490.4275 4682.7176)
      (11491.0229 4677.9847) (11491.8779 4671.6641) (11493.542 4665.3588) (11496.0916 4660.7328) (11499.2366 4659.0382)
      (11502.3817 4660.7328) (11504.9313 4665.3588) (11506.5954 4671.6641) (11507.4504 4677.9847) (11508.0458 4682.7176)
      (11509.1145 4684.8092) (11511.3588 4684.0763) (11515.1145 4681.145) (11520.1832 4677.2977) (11525.8168 4674.0153)
      (11530.9008 4672.5496) (11534.3206 4673.5725) (11535.3435 4676.9924) (11533.8779 4682.0763) (11530.5954 4687.7099)
      (11526.7328 4692.7786) (11523.8015 4696.5344) (11523.0687 4698.7786) (11525.1756 4699.8473) (11529.9084 4700.4275)
      (11536.229 4701.2977) (11542.5344 4702.9618) (11547.1603 4705.5115) (11548.855 4708.6565) (11547.1603 4711.8015)
      (11542.5344 4714.3511) (11536.229 4716.0153) (11529.9084 4716.8702) (11525.1756 4717.4656) (11523.0687 4718.5344)
      (11523.8015 4720.7786) (11526.7328 4724.5344) (11530.5954 4729.6031) (11533.8779 4735.2366) (11535.3435 4740.3206)
      (11534.3206 4743.7405) (11530.9008 4744.7634) (11525.8168 4743.2977) (11520.1832 4740.0153) (11515.1145 4736.1527)
      (11511.3588 4733.2214) (11509.1145 4732.4885) (11508.0458 4734.5954) (11507.4504 4739.3282) (11506.5954 4745.6336)
      (11504.9313 4751.9389) (11502.3817 4756.5802) (11499.2366 4758.2748) (11496.0916 4756.5802) (11493.542 4751.9389)
      (11491.8779 4745.6336) (11491.0229 4739.3282) (11490.4275 4734.5954) (11489.3588 4732.4885) (11487.1145 4733.2214)
      (11483.3588 4736.1527) (11478.2901 4740.0153) (11472.6565 4743.2977) (11467.5725 4744.7634) (11464.1527 4743.7405)
      (11463.1298 4740.3206) (11464.5954 4735.2366) (11467.8779 4729.6031) (11471.7405 4724.5344) (11474.6718 4720.7786)
      (11475.4046 4718.5344) (11473.2977 4717.4656) (11468.5649 4716.8702) (11462.2443 4716.0153) (11455.9389 4714.3511)
      (11451.313 4711.8015)
    ))
    ; P2845 -- see feature_dimensions_mm.csv
    ("06_ORNAMENT" 1 (
      (11449.6183 4085.7557) (11451.313 4082.6107) (11455.9389 4080.0611) (11462.2443 4078.3969) (11468.5649 4077.5267)
      (11473.2977 4076.9466) (11475.4046 4075.8779) (11474.6718 4073.6336) (11471.7405 4069.8779) (11467.8779 4064.8092)
      (11464.5954 4059.1756) (11463.1298 4054.0916) (11464.1527 4050.6718) (11467.5725 4049.6489) (11472.6565 4051.1145)
      (11478.2901 4054.3969) (11483.3588 4058.2595) (11487.1145 4061.1756) (11489.3588 4061.9084) (11490.4275 4059.8168)
      (11491.0229 4055.084) (11491.8779 4048.7634) (11493.542 4042.458) (11496.0916 4037.8321) (11499.2366 4036.1374)
      (11502.3817 4037.8321) (11504.9313 4042.458) (11506.5954 4048.7634) (11507.4504 4055.084) (11508.0458 4059.8168)
      (11509.1145 4061.9084) (11511.3588 4061.1756) (11515.1145 4058.2595) (11520.1832 4054.3969) (11525.8168 4051.1145)
      (11530.9008 4049.6489) (11534.3206 4050.6718) (11535.3435 4054.0916) (11533.8779 4059.1756) (11530.5954 4064.8092)
      (11526.7328 4069.8779) (11523.8015 4073.6336) (11523.0687 4075.8779) (11525.1756 4076.9466) (11529.9084 4077.5267)
      (11536.229 4078.3969) (11542.5344 4080.0611) (11547.1603 4082.6107) (11548.855 4085.7557) (11547.1603 4088.9008)
      (11542.5344 4091.4504) (11536.229 4093.1145) (11529.9084 4093.9695) (11525.1756 4094.5649) (11523.0687 4095.6336)
      (11523.8015 4097.8779) (11526.7328 4101.6336) (11530.5954 4106.7023) (11533.8779 4112.3359) (11535.3435 4117.4198)
      (11534.3206 4120.8397) (11530.9008 4121.8626) (11525.8168 4120.3969) (11520.1832 4117.1145) (11515.1145 4113.2519)
      (11511.3588 4110.3206) (11509.1145 4109.5878) (11508.0458 4111.6947) (11507.4504 4116.4275) (11506.5954 4122.7328)
      (11504.9313 4129.0382) (11502.3817 4133.6794) (11499.2366 4135.374) (11496.0916 4133.6794) (11493.542 4129.0382)
      (11491.8779 4122.7328) (11491.0229 4116.4275) (11490.4275 4111.6947) (11489.3588 4109.5878) (11487.1145 4110.3206)
      (11483.3588 4113.2519) (11478.2901 4117.1145) (11472.6565 4120.3969) (11467.5725 4121.8626) (11464.1527 4120.8397)
      (11463.1298 4117.4198) (11464.5954 4112.3359) (11467.8779 4106.7023) (11471.7405 4101.6336) (11474.6718 4097.8779)
      (11475.4046 4095.6336) (11473.2977 4094.5649) (11468.5649 4093.9695) (11462.2443 4093.1145) (11455.9389 4091.4504)
      (11451.313 4088.9008)
    ))
    ; P2846 -- see feature_dimensions_mm.csv
    ("06_ORNAMENT" 1 (
      (11464.5496 1801.5267) (11484.855 1799.1756) (11505.2366 1799.6031) (11525.5115 1802.5649) (11545.5115 1807.8015)
      (11565.0382 1815.084) (11583.9084 1824.1679) (11601.9542 1834.7786) (11618.9618 1846.6718) (11634.7786 1859.6183)
      (11649.2061 1873.3588) (11662.0458 1887.6489) (11673.145 1902.229) (11682.2901 1916.8702) (11689.3282 1931.2977)
      (11672.0 1931.6794) (11653.7099 1930.458) (11634.7176 1927.6794) (11615.3588 1923.3588) (11595.8931 1917.542)
      (11576.6107 1910.229) (11557.8321 1901.4504) (11539.8168 1891.2519) (11522.8855 1879.6641) (11507.3282 1866.6718)
      (11493.4046 1852.3511) (11481.4504 1836.7023) (11471.7405 1819.7405)
    ))
    ; P2847 -- see feature_dimensions_mm.csv
    ("06_ORNAMENT" 1 (
      (11464.5496 1679.3893) (11472.6565 1660.6412) (11483.2214 1643.1908) (11495.9237 1627.1145) (11510.4733 1612.4275)
      (11526.5344 1599.145) (11543.8321 1587.3435) (11562.0458 1577.0229) (11580.855 1568.2443) (11599.9847 1561.0229)
      (11619.084 1555.4046) (11637.8931 1551.4046) (11656.0611 1549.0992) (11673.313 1548.4885) (11689.3282 1549.6183)
      (11680.9924 1564.8092) (11670.7786 1580.0458) (11658.8855 1595.084) (11645.4656 1609.7099) (11630.687 1623.6489)
      (11614.7176 1636.687) (11597.7405 1648.5802) (11579.8931 1659.0687) (11561.3893 1667.9389) (11542.3664 1674.9313)
      (11522.9924 1679.8015) (11503.4656 1682.3359) (11483.9237 1682.2748)
    ))
    ; P2848 -- see feature_dimensions_mm.csv
    ("06_ORNAMENT" 1 (
      (11465.6489 6000.0) (11467.8931 5985.8473) (11474.3969 5973.084) (11484.5344 5962.9466) (11497.2977 5956.4427)
      (11511.4504 5954.1985) (11525.6031 5956.4427) (11538.3664 5962.9466) (11548.5038 5973.084) (11555.0076 5985.8473)
      (11557.2519 6000.0) (11555.0076 6014.1527) (11548.5038 6026.916) (11538.3664 6037.0534) (11525.6031 6043.5573)
      (11511.4504 6045.8015) (11497.2977 6043.5573) (11484.5344 6037.0534) (11474.3969 6026.916) (11467.8931 6014.1527)
    ))
    ; P2849 -- see feature_dimensions_mm.csv
    ("06_ORNAMENT" 1 (
      (11480.916 5097.9695) (11499.2366 5077.3588) (11517.5573 5097.9695) (11499.2366 5118.5802)
    ))
    ; P2850 -- see feature_dimensions_mm.csv
    ("06_ORNAMENT" 1 (
      (11480.916 4786.5191) (11499.2366 4765.9084) (11517.5573 4786.5191) (11499.2366 4807.1298)
    ))
    ; P2851 -- see feature_dimensions_mm.csv
    ("06_ORNAMENT" 1 (
      (11480.916 4163.6183) (11499.2366 4143.0076) (11517.5573 4163.6183) (11499.2366 4184.229)
    ))
    ; P2852 -- see feature_dimensions_mm.csv
    ("06_ORNAMENT" 1 (
      (11480.916 1740.458) (11497.313 1728.2748) (11515.1756 1718.4427) (11534.229 1710.8702) (11554.1679 1705.4198)
      (11574.7176 1701.9695) (11595.6031 1700.3817) (11616.5344 1700.5496) (11637.2214 1702.3511) (11657.3893 1705.6641)
      (11676.7481 1710.3511) (11695.0229 1716.2901) (11711.9237 1723.374) (11727.1603 1731.4656) (11740.458 1740.458)
      (11725.6489 1749.4504) (11709.1908 1757.542) (11691.3588 1764.626) (11672.4275 1770.5649) (11652.6565 1775.2519)
      (11632.3206 1778.5649) (11611.6641 1780.3664) (11590.9618 1780.5344) (11570.5038 1778.9466) (11550.5344 1775.4962)
      (11531.313 1770.0458) (11513.1298 1762.4733) (11496.2443 1752.6412)
    ))
    ; P2853 -- see feature_dimensions_mm.csv
    ("06_ORNAMENT" 1 (
      (11487.3282 5331.5573) (11488.229 5326.9924) (11490.8092 5323.1298) (11494.687 5320.5496) (11499.2366 5319.6489)
      (11503.7863 5320.5496) (11507.6641 5323.1298) (11510.2443 5326.9924) (11511.145 5331.5573) (11510.2443 5336.1069)
      (11507.6641 5339.9695) (11503.7863 5342.5496) (11499.2366 5343.4656) (11494.687 5342.5496) (11490.8092 5339.9695)
      (11488.229 5336.1069)
    ))
    ; P2854 -- see feature_dimensions_mm.csv
    ("06_ORNAMENT" 1 (
      (11487.3282 5020.1069) (11488.229 5015.542) (11490.8092 5011.6794) (11494.687 5009.0992) (11499.2366 5008.1985)
      (11503.7863 5009.0992) (11507.6641 5011.6794) (11510.2443 5015.542) (11511.145 5020.1069) (11510.2443 5024.6565)
      (11507.6641 5028.5191) (11503.7863 5031.0992) (11499.2366 5032.0153) (11494.687 5031.0992) (11490.8092 5028.5191)
      (11488.229 5024.6565)
    ))
    ; P2855 -- see feature_dimensions_mm.csv
    ("06_ORNAMENT" 1 (
      (11487.3282 4708.6565) (11488.229 4704.0916) (11490.8092 4700.229) (11494.687 4697.6489) (11499.2366 4696.7481)
      (11503.7863 4697.6489) (11507.6641 4700.229) (11510.2443 4704.0916) (11511.145 4708.6565) (11510.2443 4713.2061)
      (11507.6641 4717.0687) (11503.7863 4719.6489) (11499.2366 4720.5649) (11494.687 4719.6489) (11490.8092 4717.0687)
      (11488.229 4713.2061)
    ))
    ; P2856 -- see feature_dimensions_mm.csv
    ("06_ORNAMENT" 1 (
      (11487.3282 4397.2061) (11488.229 4392.6412) (11490.8092 4388.7786) (11494.687 4386.1985) (11499.2366 4385.2977)
      (11503.7863 4386.1985) (11507.6641 4388.7786) (11510.2443 4392.6412) (11511.145 4397.2061) (11510.2443 4401.7557)
      (11507.6641 4405.6183) (11503.7863 4408.1985) (11499.2366 4409.1145) (11494.687 4408.1985) (11490.8092 4405.6183)
      (11488.229 4401.7557)
    ))
    ; P2857 -- see feature_dimensions_mm.csv
    ("06_ORNAMENT" 1 (
      (11487.3282 4085.7557) (11488.229 4081.1908) (11490.8092 4077.3282) (11494.687 4074.7481) (11499.2366 4073.8473)
      (11503.7863 4074.7481) (11507.6641 4077.3282) (11510.2443 4081.1908) (11511.145 4085.7557) (11510.2443 4090.3053)
      (11507.6641 4094.1679) (11503.7863 4096.7481) (11499.2366 4097.6641) (11494.687 4096.7481) (11490.8092 4094.1679)
      (11488.229 4090.3053)
    ))
    ; P2858 -- see feature_dimensions_mm.csv
    ("06_ORNAMENT" 1 (
      (11526.7176 7374.0458) (11587.7863 7343.5115) (11648.855 7374.0458) (11587.7863 7404.5802)
    ))
    ; P2859 -- see feature_dimensions_mm.csv
    ("06_ORNAMENT" 1 (
      (11526.7176 7282.4427) (11587.7863 7251.9084) (11648.855 7282.4427) (11587.7863 7312.9771)
    ))
    ; P2860 -- see feature_dimensions_mm.csv
    ("06_ORNAMENT" 1 (
      (11526.7176 7190.8397) (11587.7863 7160.3053) (11648.855 7190.8397) (11587.7863 7221.374)
    ))
    ; P2861 -- see feature_dimensions_mm.csv
    ("06_ORNAMENT" 1 (
      (11527.4809 5175.8321) (11529.1756 5172.687) (11533.8015 5170.1374) (11540.1069 5168.4733) (11546.4275 5167.6031)
      (11551.1603 5167.0229) (11553.2672 5165.9542) (11552.5344 5163.7099) (11549.6031 5159.9542) (11545.7405 5154.8855)
      (11542.458 5149.2519) (11540.9924 5144.1679) (11542.0153 5140.7481) (11545.4351 5139.7252) (11550.5191 5141.1908)
      (11556.1527 5144.4733) (11561.2214 5148.3206) (11564.9771 5151.2519) (11567.2214 5151.9847) (11568.2901 5149.8931)
      (11568.8855 5145.1603) (11569.7405 5138.8397) (11571.4046 5132.5344) (11573.9542 5127.9084) (11577.0992 5126.2137)
      (11580.2443 5127.9084) (11582.7939 5132.5344) (11584.458 5138.8397) (11585.313 5145.1603) (11585.9084 5149.8931)
      (11586.9771 5151.9847) (11589.2214 5151.2519) (11592.9771 5148.3206) (11598.0458 5144.4733) (11603.6794 5141.1908)
      (11608.7634 5139.7252) (11612.1832 5140.7481) (11613.2061 5144.1679) (11611.7405 5149.2519) (11608.458 5154.8855)
      (11604.5954 5159.9542) (11601.6641 5163.7099) (11600.9313 5165.9542) (11603.0382 5167.0229) (11607.771 5167.6031)
      (11614.0916 5168.4733) (11620.3969 5170.1374) (11625.0229 5172.687) (11626.7176 5175.8321) (11625.0229 5178.9771)
      (11620.3969 5181.5267) (11614.0916 5183.1908) (11607.771 5184.0458) (11603.0382 5184.6412) (11600.9313 5185.7099)
      (11601.6641 5187.9542) (11604.5954 5191.7099) (11608.458 5196.7786) (11611.7405 5202.4122) (11613.2061 5207.4962)
      (11612.1832 5210.916) (11608.7634 5211.9389) (11603.6794 5210.4733) (11598.0458 5207.1908) (11592.9771 5203.3282)
      (11589.2214 5200.3969) (11586.9771 5199.6641) (11585.9084 5201.771) (11585.313 5206.5038) (11584.458 5212.8092)
      (11582.7939 5219.1145) (11580.2443 5223.7557) (11577.0992 5225.4504) (11573.9542 5223.7557) (11571.4046 5219.1145)
      (11569.7405 5212.8092) (11568.8855 5206.5038) (11568.2901 5201.771) (11567.2214 5199.6641) (11564.9771 5200.3969)
      (11561.2214 5203.3282) (11556.1527 5207.1908) (11550.5191 5210.4733) (11545.4351 5211.9389) (11542.0153 5210.916)
      (11540.9924 5207.4962) (11542.458 5202.4122) (11545.7405 5196.7786) (11549.6031 5191.7099) (11552.5344 5187.9542)
      (11553.2672 5185.7099) (11551.1603 5184.6412) (11546.4275 5184.0458) (11540.1069 5183.1908) (11533.8015 5181.5267)
      (11529.1756 5178.9771)
    ))
    ; P2862 -- see feature_dimensions_mm.csv
    ("06_ORNAMENT" 1 (
      (11527.4809 4864.3817) (11529.1756 4861.2366) (11533.8015 4858.687) (11540.1069 4857.0229) (11546.4275 4856.1527)
      (11551.1603 4855.5725) (11553.2672 4854.5038) (11552.5344 4852.2595) (11549.6031 4848.5038) (11545.7405 4843.4351)
      (11542.458 4837.8015) (11540.9924 4832.7176) (11542.0153 4829.2977) (11545.4351 4828.2748) (11550.5191 4829.7405)
      (11556.1527 4833.0229) (11561.2214 4836.8702) (11564.9771 4839.8015) (11567.2214 4840.5344) (11568.2901 4838.4427)
      (11568.8855 4833.7099) (11569.7405 4827.3893) (11571.4046 4821.084) (11573.9542 4816.458) (11577.0992 4814.7634)
      (11580.2443 4816.458) (11582.7939 4821.084) (11584.458 4827.3893) (11585.313 4833.7099) (11585.9084 4838.4427)
      (11586.9771 4840.5344) (11589.2214 4839.8015) (11592.9771 4836.8702) (11598.0458 4833.0229) (11603.6794 4829.7405)
      (11608.7634 4828.2748) (11612.1832 4829.2977) (11613.2061 4832.7176) (11611.7405 4837.8015) (11608.458 4843.4351)
      (11604.5954 4848.5038) (11601.6641 4852.2595) (11600.9313 4854.5038) (11603.0382 4855.5725) (11607.771 4856.1527)
      (11614.0916 4857.0229) (11620.3969 4858.687) (11625.0229 4861.2366) (11626.7176 4864.3817) (11625.0229 4867.5267)
      (11620.3969 4870.0763) (11614.0916 4871.7405) (11607.771 4872.5954) (11603.0382 4873.1908) (11600.9313 4874.2595)
      (11601.6641 4876.5038) (11604.5954 4880.2595) (11608.458 4885.3282) (11611.7405 4890.9618) (11613.2061 4896.0458)
      (11612.1832 4899.4656) (11608.7634 4900.4885) (11603.6794 4899.0229) (11598.0458 4895.7405) (11592.9771 4891.8779)
      (11589.2214 4888.9466) (11586.9771 4888.2137) (11585.9084 4890.3206) (11585.313 4895.0534) (11584.458 4901.3588)
      (11582.7939 4907.6641) (11580.2443 4912.3053) (11577.0992 4914.0) (11573.9542 4912.3053) (11571.4046 4907.6641)
      (11569.7405 4901.3588) (11568.8855 4895.0534) (11568.2901 4890.3206) (11567.2214 4888.2137) (11564.9771 4888.9466)
      (11561.2214 4891.8779) (11556.1527 4895.7405) (11550.5191 4899.0229) (11545.4351 4900.4885) (11542.0153 4899.4656)
      (11540.9924 4896.0458) (11542.458 4890.9618) (11545.7405 4885.3282) (11549.6031 4880.2595) (11552.5344 4876.5038)
      (11553.2672 4874.2595) (11551.1603 4873.1908) (11546.4275 4872.5954) (11540.1069 4871.7405) (11533.8015 4870.0763)
      (11529.1756 4867.5267)
    ))
    ; P2863 -- see feature_dimensions_mm.csv
    ("06_ORNAMENT" 1 (
      (11527.4809 4552.9313) (11529.1756 4549.7863) (11533.8015 4547.2366) (11540.1069 4545.5725) (11546.4275 4544.7023)
      (11551.1603 4544.1221) (11553.2672 4543.0534) (11552.5344 4540.8092) (11549.6031 4537.0534) (11545.7405 4531.9847)
      (11542.458 4526.3511) (11540.9924 4521.2672) (11542.0153 4517.8473) (11545.4351 4516.8244) (11550.5191 4518.2901)
      (11556.1527 4521.5725) (11561.2214 4525.4198) (11564.9771 4528.3511) (11567.2214 4529.084) (11568.2901 4526.9924)
      (11568.8855 4522.2595) (11569.7405 4515.9389) (11571.4046 4509.6336) (11573.9542 4505.0076) (11577.0992 4503.313)
      (11580.2443 4505.0076) (11582.7939 4509.6336) (11584.458 4515.9389) (11585.313 4522.2595) (11585.9084 4526.9924)
      (11586.9771 4529.084) (11589.2214 4528.3511) (11592.9771 4525.4198) (11598.0458 4521.5725) (11603.6794 4518.2901)
      (11608.7634 4516.8244) (11612.1832 4517.8473) (11613.2061 4521.2672) (11611.7405 4526.3511) (11608.458 4531.9847)
      (11604.5954 4537.0534) (11601.6641 4540.8092) (11600.9313 4543.0534) (11603.0382 4544.1221) (11607.771 4544.7023)
      (11614.0916 4545.5725) (11620.3969 4547.2366) (11625.0229 4549.7863) (11626.7176 4552.9313) (11625.0229 4556.0763)
      (11620.3969 4558.626) (11614.0916 4560.2901) (11607.771 4561.145) (11603.0382 4561.7405) (11600.9313 4562.8092)
      (11601.6641 4565.0534) (11604.5954 4568.8092) (11608.458 4573.8779) (11611.7405 4579.5115) (11613.2061 4584.5954)
      (11612.1832 4588.0153) (11608.7634 4589.0382) (11603.6794 4587.5725) (11598.0458 4584.2901) (11592.9771 4580.4275)
      (11589.2214 4577.4962) (11586.9771 4576.7634) (11585.9084 4578.8702) (11585.313 4583.6031) (11584.458 4589.9084)
      (11582.7939 4596.2137) (11580.2443 4600.855) (11577.0992 4602.5496) (11573.9542 4600.855) (11571.4046 4596.2137)
      (11569.7405 4589.9084) (11568.8855 4583.6031) (11568.2901 4578.8702) (11567.2214 4576.7634) (11564.9771 4577.4962)
      (11561.2214 4580.4275) (11556.1527 4584.2901) (11550.5191 4587.5725) (11545.4351 4589.0382) (11542.0153 4588.0153)
      (11540.9924 4584.5954) (11542.458 4579.5115) (11545.7405 4573.8779) (11549.6031 4568.8092) (11552.5344 4565.0534)
      (11553.2672 4562.8092) (11551.1603 4561.7405) (11546.4275 4561.145) (11540.1069 4560.2901) (11533.8015 4558.626)
      (11529.1756 4556.0763)
    ))
    ; P2864 -- see feature_dimensions_mm.csv
    ("06_ORNAMENT" 1 (
      (11527.4809 4241.4809) (11529.1756 4238.3359) (11533.8015 4235.7863) (11540.1069 4234.1221) (11546.4275 4233.2519)
      (11551.1603 4232.6718) (11553.2672 4231.6031) (11552.5344 4229.3588) (11549.6031 4225.6031) (11545.7405 4220.5344)
      (11542.458 4214.9008) (11540.9924 4209.8168) (11542.0153 4206.3969) (11545.4351 4205.374) (11550.5191 4206.8397)
      (11556.1527 4210.1221) (11561.2214 4213.9695) (11564.9771 4216.9008) (11567.2214 4217.6336) (11568.2901 4215.542)
      (11568.8855 4210.8092) (11569.7405 4204.4885) (11571.4046 4198.1832) (11573.9542 4193.5573) (11577.0992 4191.8626)
      (11580.2443 4193.5573) (11582.7939 4198.1832) (11584.458 4204.4885) (11585.313 4210.8092) (11585.9084 4215.542)
      (11586.9771 4217.6336) (11589.2214 4216.9008) (11592.9771 4213.9695) (11598.0458 4210.1221) (11603.6794 4206.8397)
      (11608.7634 4205.374) (11612.1832 4206.3969) (11613.2061 4209.8168) (11611.7405 4214.9008) (11608.458 4220.5344)
      (11604.5954 4225.6031) (11601.6641 4229.3588) (11600.9313 4231.6031) (11603.0382 4232.6718) (11607.771 4233.2519)
      (11614.0916 4234.1221) (11620.3969 4235.7863) (11625.0229 4238.3359) (11626.7176 4241.4809) (11625.0229 4244.626)
      (11620.3969 4247.1756) (11614.0916 4248.8397) (11607.771 4249.6947) (11603.0382 4250.2901) (11600.9313 4251.3588)
      (11601.6641 4253.6031) (11604.5954 4257.3588) (11608.458 4262.4275) (11611.7405 4268.0611) (11613.2061 4273.145)
      (11612.1832 4276.5649) (11608.7634 4277.5878) (11603.6794 4276.1221) (11598.0458 4272.8397) (11592.9771 4268.9771)
      (11589.2214 4266.0458) (11586.9771 4265.313) (11585.9084 4267.4198) (11585.313 4272.1527) (11584.458 4278.458)
      (11582.7939 4284.7634) (11580.2443 4289.4046) (11577.0992 4291.0992) (11573.9542 4289.4046) (11571.4046 4284.7634)
      (11569.7405 4278.458) (11568.8855 4272.1527) (11568.2901 4267.4198) (11567.2214 4265.313) (11564.9771 4266.0458)
      (11561.2214 4268.9771) (11556.1527 4272.8397) (11550.5191 4276.1221) (11545.4351 4277.5878) (11542.0153 4276.5649)
      (11540.9924 4273.145) (11542.458 4268.0611) (11545.7405 4262.4275) (11549.6031 4257.3588) (11552.5344 4253.6031)
      (11553.2672 4251.3588) (11551.1603 4250.2901) (11546.4275 4249.6947) (11540.1069 4248.8397) (11533.8015 4247.1756)
      (11529.1756 4244.626)
    ))
    ; P2865 -- see feature_dimensions_mm.csv
    ("06_ORNAMENT" 1 (
      (11527.4809 3930.0305) (11529.1756 3926.8855) (11533.8015 3924.3359) (11540.1069 3922.6718) (11546.4275 3921.8015)
      (11551.1603 3921.2214) (11553.2672 3920.1527) (11552.5344 3917.9084) (11549.6031 3914.1527) (11545.7405 3909.084)
      (11542.458 3903.4504) (11540.9924 3898.3664) (11542.0153 3894.9466) (11545.4351 3893.9237) (11550.5191 3895.3893)
      (11556.1527 3898.6718) (11561.2214 3902.5191) (11564.9771 3905.4504) (11567.2214 3906.1832) (11568.2901 3904.0916)
      (11568.8855 3899.3588) (11569.7405 3893.0382) (11571.4046 3886.7328) (11573.9542 3882.1069) (11577.0992 3880.4122)
      (11580.2443 3882.1069) (11582.7939 3886.7328) (11584.458 3893.0382) (11585.313 3899.3588) (11585.9084 3904.0916)
      (11586.9771 3906.1832) (11589.2214 3905.4504) (11592.9771 3902.5191) (11598.0458 3898.6718) (11603.6794 3895.3893)
      (11608.7634 3893.9237) (11612.1832 3894.9466) (11613.2061 3898.3664) (11611.7405 3903.4504) (11608.458 3909.084)
      (11604.5954 3914.1527) (11601.6641 3917.9084) (11600.9313 3920.1527) (11603.0382 3921.2214) (11607.771 3921.8015)
      (11614.0916 3922.6718) (11620.3969 3924.3359) (11625.0229 3926.8855) (11626.7176 3930.0305) (11625.0229 3933.1756)
      (11620.3969 3935.7252) (11614.0916 3937.3893) (11607.771 3938.2443) (11603.0382 3938.8397) (11600.9313 3939.9084)
      (11601.6641 3942.1527) (11604.5954 3945.9084) (11608.458 3950.9771) (11611.7405 3956.6107) (11613.2061 3961.6947)
      (11612.1832 3965.1145) (11608.7634 3966.1374) (11603.6794 3964.6718) (11598.0458 3961.3893) (11592.9771 3957.5267)
      (11589.2214 3954.5954) (11586.9771 3953.8626) (11585.9084 3955.9695) (11585.313 3960.7023) (11584.458 3967.0076)
      (11582.7939 3973.313) (11580.2443 3977.9542) (11577.0992 3979.6489) (11573.9542 3977.9542) (11571.4046 3973.313)
      (11569.7405 3967.0076) (11568.8855 3960.7023) (11568.2901 3955.9695) (11567.2214 3953.8626) (11564.9771 3954.5954)
      (11561.2214 3957.5267) (11556.1527 3961.3893) (11550.5191 3964.6718) (11545.4351 3966.1374) (11542.0153 3965.1145)
      (11540.9924 3961.6947) (11542.458 3956.6107) (11545.7405 3950.9771) (11549.6031 3945.9084) (11552.5344 3942.1527)
      (11553.2672 3939.9084) (11551.1603 3938.8397) (11546.4275 3938.2443) (11540.1069 3937.3893) (11533.8015 3935.7252)
      (11529.1756 3933.1756)
    ))
    ; P2866 -- see feature_dimensions_mm.csv
    ("06_ORNAMENT" 1 (
      (11557.2519 2137.4046) (11558.4885 2133.4809) (11562.0305 2130.0) (11567.2977 2127.2519) (11573.4962 2125.3893)
      (11579.6794 2124.2901) (11585.0229 2123.6031) (11588.8397 2122.8702) (11590.8244 2121.5267) (11590.9924 2119.145)
      (11589.7252 2115.4656) (11587.6489 2110.5038) (11585.4962 2104.5802) (11584.0153 2098.2901) (11583.7557 2092.3664)
      (11585.0076 2087.5573) (11587.7863 2084.5191) (11591.8015 2083.6336) (11596.5954 2084.9466) (11601.6031 2088.1374)
      (11606.3053 2092.5802) (11610.3664 2097.3893) (11613.6183 2101.6641) (11616.1679 2104.6107) (11618.3206 2105.6489)
      (11620.4733 2104.6107) (11623.0229 2101.6641) (11626.2748 2097.3893) (11630.3359 2092.5802) (11635.0382 2088.1374)
      (11640.0458 2084.9466) (11644.8397 2083.6336) (11648.855 2084.5191) (11651.6336 2087.5573) (11652.8855 2092.3664)
      (11652.626 2098.2901) (11651.145 2104.5802) (11648.9924 2110.5038) (11646.916 2115.4656) (11645.6489 2119.145)
      (11645.8168 2121.5267) (11647.8015 2122.8702) (11651.6183 2123.6031) (11656.9618 2124.2901) (11663.145 2125.3893)
      (11669.3435 2127.2519) (11674.6107 2130.0) (11678.1527 2133.4809) (11679.3893 2137.4046) (11678.1527 2141.3282)
      (11674.6107 2144.8092) (11669.3435 2147.5573) (11663.145 2149.4198) (11656.9618 2150.5191) (11651.6183 2151.2061)
      (11647.8015 2151.9389) (11645.8168 2153.2824) (11645.6489 2155.6641) (11646.916 2159.3435) (11648.9924 2164.3053)
      (11651.145 2170.229) (11652.1679 2174.5954) (11637.6031 2185.8473) (11635.7252 2187.0992) (11635.0382 2186.6718)
      (11630.3359 2182.229) (11626.2748 2177.4198) (11623.0229 2173.145) (11620.4733 2170.1985) (11618.3206 2169.1603)
      (11616.1679 2170.1985) (11613.6183 2173.145) (11610.3664 2177.4198) (11606.3053 2182.229) (11601.6031 2186.6718)
      (11596.5954 2189.8626) (11591.8015 2191.1756) (11587.7863 2190.2901) (11585.0076 2187.2519) (11583.7557 2182.4427)
      (11584.0153 2176.5191) (11585.4962 2170.229) (11587.6489 2164.3053) (11589.7252 2159.3435) (11590.9924 2155.6641)
      (11590.8244 2153.2824) (11588.8397 2151.9389) (11585.0229 2151.2061) (11579.6794 2150.5191) (11573.4962 2149.4198)
      (11567.2977 2147.5573) (11562.0305 2144.8092) (11558.4885 2141.3282)
    ))
    ; P2867 -- see feature_dimensions_mm.csv
    ("06_ORNAMENT" 1 (
      (11557.2519 1374.0458) (11558.4885 1370.1221) (11562.0305 1366.6412) (11567.2977 1363.8931) (11573.4962 1362.0305)
      (11579.6794 1360.9313) (11585.0229 1360.2443) (11588.8397 1359.5115) (11590.8244 1358.1679) (11590.9924 1355.7863)
      (11589.7252 1352.1069) (11587.6489 1347.145) (11585.4962 1341.2214) (11584.0153 1334.9313) (11583.7557 1329.0076)
      (11585.0076 1324.1985) (11587.7863 1321.1603) (11591.8015 1320.2748) (11596.5954 1321.5878) (11601.6031 1324.7786)
      (11606.3053 1329.2214) (11610.3664 1334.0305) (11613.6183 1338.3053) (11616.1679 1341.2519) (11618.3206 1342.2901)
      (11620.4733 1341.2519) (11623.0229 1338.3053) (11626.2748 1334.0305) (11630.3359 1329.2214) (11635.0382 1324.7786)
      (11640.0458 1321.5878) (11644.8397 1320.2748) (11648.855 1321.1603) (11651.6336 1324.1985) (11652.8855 1329.0076)
      (11652.626 1334.9313) (11651.145 1341.2214) (11648.9924 1347.145) (11646.916 1352.1069) (11645.6489 1355.7863)
      (11645.8168 1358.1679) (11647.8015 1359.5115) (11651.6183 1360.2443) (11656.9618 1360.9313) (11663.145 1362.0305)
      (11669.3435 1363.8931) (11674.6107 1366.6412) (11678.1527 1370.1221) (11679.3893 1374.0458) (11678.1527 1377.9695)
      (11674.6107 1381.4504) (11669.3435 1384.1985) (11663.145 1386.0611) (11656.9618 1387.1603) (11651.6183 1387.8473)
      (11647.8015 1388.5802) (11645.8168 1389.9237) (11645.6489 1392.3053) (11646.916 1395.9847) (11648.9924 1400.9466)
      (11651.145 1406.8702) (11652.626 1413.1603) (11652.6565 1413.9237) (11653.4809 1413.3435) (11663.7099 1407.4809)
      (11674.0763 1402.6565) (11684.4122 1398.916) (11694.5191 1396.3511) (11704.229 1395.0076) (11702.2595 1405.3435)
      (11699.1908 1415.9542) (11695.0687 1426.6718) (11689.9695 1437.313) (11683.9237 1447.7252) (11676.9924 1457.7252)
      (11669.2519 1467.1603) (11660.7176 1475.8473) (11651.4656 1483.6183) (11641.5573 1490.3206) (11631.0229 1495.771)
      (11619.9237 1499.8015) (11608.3359 1502.2595) (11596.2748 1502.9618) (11597.4198 1490.458) (11600.2901 1478.458)
      (11604.6718 1467.0076) (11610.4275 1456.1679) (11617.374 1446.0153) (11625.313 1436.5954) (11634.1069 1427.9695)
      (11637.7099 1425.0076) (11635.0382 1423.313) (11630.3359 1418.8702) (11626.2748 1414.0611) (11623.0229 1409.7863)
      (11620.4733 1406.8397) (11618.3206 1405.8015) (11616.1679 1406.8397) (11613.6183 1409.7863) (11610.3664 1414.0611)
      (11606.3053 1418.8702) (11601.6031 1423.313) (11596.5954 1426.5038) (11591.8015 1427.8168) (11587.7863 1426.9313)
      (11585.0076 1423.8931) (11583.7557 1419.084) (11584.0153 1413.1603) (11585.4962 1406.8702) (11587.6489 1400.9466)
      (11589.7252 1395.9847) (11590.9924 1392.3053) (11590.8244 1389.9237) (11588.8397 1388.5802) (11585.0229 1387.8473)
      (11579.6794 1387.1603) (11573.4962 1386.0611) (11567.2977 1384.1985) (11562.0305 1381.4504) (11558.4885 1377.9695)
    ))
    ; P2868 -- see feature_dimensions_mm.csv
    ("06_ORNAMENT" 1 (
      (11558.7786 5253.6947) (11577.0992 5233.084) (11595.4198 5253.6947) (11577.0992 5274.3053)
    ))
    ; P2869 -- see feature_dimensions_mm.csv
    ("06_ORNAMENT" 1 (
      (11558.7786 4942.2443) (11577.0992 4921.6336) (11595.4198 4942.2443) (11577.0992 4962.855)
    ))
    ; P2870 -- see feature_dimensions_mm.csv
    ("06_ORNAMENT" 1 (
      (11558.7786 4630.7939) (11577.0992 4610.1832) (11595.4198 4630.7939) (11577.0992 4651.4046)
    ))
    ; P2871 -- see feature_dimensions_mm.csv
    ("06_ORNAMENT" 1 (
      (11558.7786 4319.3435) (11577.0992 4298.7328) (11595.4198 4319.3435) (11577.0992 4339.9542)
    ))
    ; P2872 -- see feature_dimensions_mm.csv
    ("06_ORNAMENT" 1 (
      (11558.7786 4007.8931) (11577.0992 3987.2824) (11595.4198 4007.8931) (11577.0992 4028.5038)
    ))
    ; P2873 -- see feature_dimensions_mm.csv
    ("06_ORNAMENT" 1 (
      (11565.1908 5175.8321) (11566.0916 5171.2672) (11568.6718 5167.4046) (11572.5496 5164.8244) (11577.0992 5163.9237)
      (11581.6489 5164.8244) (11585.5267 5167.4046) (11588.1069 5171.2672) (11589.0076 5175.8321) (11588.1069 5180.3817)
      (11585.5267 5184.2443) (11581.6489 5186.8244) (11577.0992 5187.7405) (11572.5496 5186.8244) (11568.6718 5184.2443)
      (11566.0916 5180.3817)
    ))
    ; P2874 -- see feature_dimensions_mm.csv
    ("06_ORNAMENT" 1 (
      (11565.1908 4864.3817) (11566.0916 4859.8168) (11568.6718 4855.9542) (11572.5496 4853.374) (11577.0992 4852.4733)
      (11581.6489 4853.374) (11585.5267 4855.9542) (11588.1069 4859.8168) (11589.0076 4864.3817) (11588.1069 4868.9313)
      (11585.5267 4872.7939) (11581.6489 4875.374) (11577.0992 4876.2901) (11572.5496 4875.374) (11568.6718 4872.7939)
      (11566.0916 4868.9313)
    ))
    ; P2875 -- see feature_dimensions_mm.csv
    ("06_ORNAMENT" 1 (
      (11565.1908 4552.9313) (11566.0916 4548.3664) (11568.6718 4544.5038) (11572.5496 4541.9237) (11577.0992 4541.0229)
      (11581.6489 4541.9237) (11585.5267 4544.5038) (11588.1069 4548.3664) (11589.0076 4552.9313) (11588.1069 4557.4809)
      (11585.5267 4561.3435) (11581.6489 4563.9237) (11577.0992 4564.8397) (11572.5496 4563.9237) (11568.6718 4561.3435)
      (11566.0916 4557.4809)
    ))
    ; P2876 -- see feature_dimensions_mm.csv
    ("06_ORNAMENT" 1 (
      (11565.1908 4241.4809) (11566.0916 4236.916) (11568.6718 4233.0534) (11572.5496 4230.4733) (11577.0992 4229.5725)
      (11581.6489 4230.4733) (11585.5267 4233.0534) (11588.1069 4236.916) (11589.0076 4241.4809) (11588.1069 4246.0305)
      (11585.5267 4249.8931) (11581.6489 4252.4733) (11577.0992 4253.3893) (11572.5496 4252.4733) (11568.6718 4249.8931)
      (11566.0916 4246.0305)
    ))
    ; P2877 -- see feature_dimensions_mm.csv
    ("06_ORNAMENT" 1 (
      (11565.1908 3930.0305) (11566.0916 3925.4656) (11568.6718 3921.6031) (11572.5496 3919.0229) (11577.0992 3918.1221)
      (11581.6489 3919.0229) (11585.5267 3921.6031) (11588.1069 3925.4656) (11589.0076 3930.0305) (11588.1069 3934.5802)
      (11585.5267 3938.4427) (11581.6489 3941.0229) (11577.0992 3941.9389) (11572.5496 3941.0229) (11568.6718 3938.4427)
      (11566.0916 3934.5802)
    ))
    ; P2878 -- see feature_dimensions_mm.csv
    ("06_ORNAMENT" 1 (
      (11596.2748 1977.9542) (11608.7786 1979.0992) (11620.7786 1981.9695) (11632.229 1986.3511) (11643.0687 1992.1069)
      (11653.2214 1999.0534) (11662.6412 2006.9924) (11671.2672 2015.7863) (11679.0382 2025.2214) (11685.8931 2035.1603)
      (11691.7557 2045.3893) (11696.5802 2055.7557) (11700.3206 2066.0916) (11702.8855 2076.1985) (11704.229 2085.9084)
      (11693.8931 2083.9389) (11683.2824 2080.8702) (11672.5649 2076.7481) (11661.9237 2071.6489) (11651.5115 2065.6031)
      (11641.5115 2058.6718) (11632.0763 2050.9313) (11623.3893 2042.3969) (11615.6183 2033.145) (11608.916 2023.2366)
      (11603.4656 2012.7023) (11599.4351 2001.6031) (11596.9771 1990.0153)
    ))
    ; P2879 -- see feature_dimensions_mm.csv
    ("06_ORNAMENT" 1 (
      (11605.3435 5331.5573) (11607.0382 5328.4122) (11611.6641 5325.8626) (11617.9695 5324.1985) (11624.2901 5323.3282)
      (11629.0229 5322.7481) (11631.1298 5321.6794) (11630.3969 5319.4351) (11627.4656 5315.6794) (11623.6031 5310.6107)
      (11620.3206 5304.9771) (11618.855 5299.8931) (11619.8779 5296.4733) (11623.2977 5295.4504) (11628.3817 5296.916)
      (11634.0153 5300.1985) (11639.084 5304.0458) (11642.8397 5306.9771) (11645.084 5307.7099) (11646.1527 5305.6183)
      (11646.7481 5300.8855) (11647.6031 5294.5649) (11649.2672 5288.2595) (11651.8168 5283.6336) (11654.9618 5281.9389)
      (11658.1069 5283.6336) (11660.6565 5288.2595) (11662.3206 5294.5649) (11663.1756 5300.8855) (11663.771 5305.6183)
      (11664.8397 5307.7099) (11667.084 5306.9771) (11670.8397 5304.0458) (11675.9084 5300.1985) (11681.542 5296.916)
      (11686.626 5295.4504) (11690.0458 5296.4733) (11691.0687 5299.8931) (11689.6031 5304.9771) (11686.3206 5310.6107)
      (11682.458 5315.6794) (11679.5267 5319.4351) (11678.7939 5321.6794) (11680.9008 5322.7481) (11685.6336 5323.3282)
      (11691.9542 5324.1985) (11698.2595 5325.8626) (11702.8855 5328.4122) (11704.5802 5331.5573) (11702.8855 5334.7023)
      (11698.2595 5337.2519) (11691.9542 5338.916) (11685.6336 5339.771) (11680.9008 5340.3664) (11678.7939 5341.4351)
      (11679.5267 5343.6794) (11682.458 5347.4351) (11686.3206 5352.5038) (11689.6031 5358.1374) (11691.0687 5363.2214)
      (11690.0458 5366.6412) (11686.626 5367.6641) (11681.542 5366.1985) (11675.9084 5362.916) (11670.8397 5359.0534)
      (11667.084 5356.1221) (11664.8397 5355.3893) (11663.771 5357.4962) (11663.1756 5362.229) (11662.3206 5368.5344)
      (11660.6565 5374.8397) (11658.1069 5379.4809) (11654.9618 5381.1756) (11651.8168 5379.4809) (11649.2672 5374.8397)
      (11647.6031 5368.5344) (11646.7481 5362.229) (11646.1527 5357.4962) (11645.084 5355.3893) (11642.8397 5356.1221)
      (11639.084 5359.0534) (11634.0153 5362.916) (11628.3817 5366.1985) (11623.2977 5367.6641) (11619.8779 5366.6412)
      (11618.855 5363.2214) (11620.3206 5358.1374) (11623.6031 5352.5038) (11627.4656 5347.4351) (11630.3969 5343.6794)
      (11631.1298 5341.4351) (11629.0229 5340.3664) (11624.2901 5339.771) (11617.9695 5338.916) (11611.6641 5337.2519)
      (11607.0382 5334.7023)
    ))
    ; P2880 -- see feature_dimensions_mm.csv
    ("06_ORNAMENT" 1 (
      (11605.3435 5020.1069) (11607.0382 5016.9618) (11611.6641 5014.4122) (11617.9695 5012.7481) (11624.2901 5011.8779)
      (11629.0229 5011.2977) (11631.1298 5010.229) (11630.3969 5007.9847) (11627.4656 5004.229) (11623.6031 4999.1603)
      (11620.3206 4993.5267) (11618.855 4988.4427) (11619.8779 4985.0229) (11623.2977 4984.0) (11628.3817 4985.4656)
      (11634.0153 4988.7481) (11639.084 4992.5954) (11642.8397 4995.5267) (11645.084 4996.2595) (11646.1527 4994.1679)
      (11646.7481 4989.4351) (11647.6031 4983.1145) (11649.2672 4976.8092) (11651.8168 4972.1832) (11654.9618 4970.4885)
      (11658.1069 4972.1832) (11660.6565 4976.8092) (11662.3206 4983.1145) (11663.1756 4989.4351) (11663.771 4994.1679)
      (11664.8397 4996.2595) (11667.084 4995.5267) (11670.8397 4992.5954) (11675.9084 4988.7481) (11681.542 4985.4656)
      (11686.626 4984.0) (11690.0458 4985.0229) (11691.0687 4988.4427) (11689.6031 4993.5267) (11686.3206 4999.1603)
      (11682.458 5004.229) (11679.5267 5007.9847) (11678.7939 5010.229) (11680.9008 5011.2977) (11685.6336 5011.8779)
      (11691.9542 5012.7481) (11698.2595 5014.4122) (11702.8855 5016.9618) (11704.5802 5020.1069) (11702.8855 5023.2519)
      (11698.2595 5025.8015) (11691.9542 5027.4656) (11685.6336 5028.3206) (11680.9008 5028.916) (11678.7939 5029.9847)
      (11679.5267 5032.229) (11682.458 5035.9847) (11686.3206 5041.0534) (11689.6031 5046.687) (11691.0687 5051.771)
      (11690.0458 5055.1908) (11686.626 5056.2137) (11681.542 5054.7481) (11675.9084 5051.4656) (11670.8397 5047.6031)
      (11667.084 5044.6718) (11664.8397 5043.9389) (11663.771 5046.0458) (11663.1756 5050.7786) (11662.3206 5057.084)
      (11660.6565 5063.3893) (11658.1069 5068.0305) (11654.9618 5069.7252) (11651.8168 5068.0305) (11649.2672 5063.3893)
      (11647.6031 5057.084) (11646.7481 5050.7786) (11646.1527 5046.0458) (11645.084 5043.9389) (11642.8397 5044.6718)
      (11639.084 5047.6031) (11634.0153 5051.4656) (11628.3817 5054.7481) (11623.2977 5056.2137) (11619.8779 5055.1908)
      (11618.855 5051.771) (11620.3206 5046.687) (11623.6031 5041.0534) (11627.4656 5035.9847) (11630.3969 5032.229)
      (11631.1298 5029.9847) (11629.0229 5028.916) (11624.2901 5028.3206) (11617.9695 5027.4656) (11611.6641 5025.8015)
      (11607.0382 5023.2519)
    ))
    ; P2881 -- see feature_dimensions_mm.csv
    ("06_ORNAMENT" 1 (
      (11605.3435 4708.6565) (11607.0382 4705.5115) (11611.6641 4702.9618) (11617.9695 4701.2977) (11624.2901 4700.4275)
      (11629.0229 4699.8473) (11631.1298 4698.7786) (11630.3969 4696.5344) (11627.4656 4692.7786) (11623.6031 4687.7099)
      (11620.3206 4682.0763) (11618.855 4676.9924) (11619.8779 4673.5725) (11623.2977 4672.5496) (11628.3817 4674.0153)
      (11634.0153 4677.2977) (11639.084 4681.145) (11642.8397 4684.0763) (11645.084 4684.8092) (11646.1527 4682.7176)
      (11646.7481 4677.9847) (11647.6031 4671.6641) (11649.2672 4665.3588) (11651.8168 4660.7328) (11654.9618 4659.0382)
      (11658.1069 4660.7328) (11660.6565 4665.3588) (11662.3206 4671.6641) (11663.1756 4677.9847) (11663.771 4682.7176)
      (11664.8397 4684.8092) (11667.084 4684.0763) (11670.8397 4681.145) (11675.9084 4677.2977) (11681.542 4674.0153)
      (11686.626 4672.5496) (11690.0458 4673.5725) (11691.0687 4676.9924) (11689.6031 4682.0763) (11686.3206 4687.7099)
      (11682.458 4692.7786) (11679.5267 4696.5344) (11678.7939 4698.7786) (11680.9008 4699.8473) (11685.6336 4700.4275)
      (11691.9542 4701.2977) (11698.2595 4702.9618) (11702.8855 4705.5115) (11704.5802 4708.6565) (11702.8855 4711.8015)
      (11698.2595 4714.3511) (11691.9542 4716.0153) (11685.6336 4716.8702) (11680.9008 4717.4656) (11678.7939 4718.5344)
      (11679.5267 4720.7786) (11682.458 4724.5344) (11686.3206 4729.6031) (11689.6031 4735.2366) (11691.0687 4740.3206)
      (11690.0458 4743.7405) (11686.626 4744.7634) (11681.542 4743.2977) (11675.9084 4740.0153) (11670.8397 4736.1527)
      (11667.084 4733.2214) (11664.8397 4732.4885) (11663.771 4734.5954) (11663.1756 4739.3282) (11662.3206 4745.6336)
      (11660.6565 4751.9389) (11658.1069 4756.5802) (11654.9618 4758.2748) (11651.8168 4756.5802) (11649.2672 4751.9389)
      (11647.6031 4745.6336) (11646.7481 4739.3282) (11646.1527 4734.5954) (11645.084 4732.4885) (11642.8397 4733.2214)
      (11639.084 4736.1527) (11634.0153 4740.0153) (11628.3817 4743.2977) (11623.2977 4744.7634) (11619.8779 4743.7405)
      (11618.855 4740.3206) (11620.3206 4735.2366) (11623.6031 4729.6031) (11627.4656 4724.5344) (11630.3969 4720.7786)
      (11631.1298 4718.5344) (11629.0229 4717.4656) (11624.2901 4716.8702) (11617.9695 4716.0153) (11611.6641 4714.3511)
      (11607.0382 4711.8015)
    ))
    ; P2882 -- see feature_dimensions_mm.csv
    ("06_ORNAMENT" 1 (
      (11605.3435 4085.7557) (11607.0382 4082.6107) (11611.6641 4080.0611) (11617.9695 4078.3969) (11624.2901 4077.5267)
      (11629.0229 4076.9466) (11631.1298 4075.8779) (11630.3969 4073.6336) (11627.4656 4069.8779) (11623.6031 4064.8092)
      (11620.3206 4059.1756) (11618.855 4054.0916) (11619.8779 4050.6718) (11623.2977 4049.6489) (11628.3817 4051.1145)
      (11634.0153 4054.3969) (11639.084 4058.2595) (11642.8397 4061.1756) (11645.084 4061.9084) (11646.1527 4059.8168)
      (11646.7481 4055.084) (11647.6031 4048.7634) (11649.2672 4042.458) (11651.8168 4037.8321) (11654.9618 4036.1374)
      (11658.1069 4037.8321) (11660.6565 4042.458) (11662.3206 4048.7634) (11663.1756 4055.084) (11663.771 4059.8168)
      (11664.8397 4061.9084) (11667.084 4061.1756) (11670.8397 4058.2595) (11675.9084 4054.3969) (11681.542 4051.1145)
      (11686.626 4049.6489) (11690.0458 4050.6718) (11691.0687 4054.0916) (11689.6031 4059.1756) (11686.3206 4064.8092)
      (11682.458 4069.8779) (11679.5267 4073.6336) (11678.7939 4075.8779) (11680.9008 4076.9466) (11685.6336 4077.5267)
      (11691.9542 4078.3969) (11698.2595 4080.0611) (11702.8855 4082.6107) (11704.5802 4085.7557) (11702.8855 4088.9008)
      (11698.2595 4091.4504) (11691.9542 4093.1145) (11685.6336 4093.9695) (11680.9008 4094.5649) (11678.7939 4095.6336)
      (11679.5267 4097.8779) (11682.458 4101.6336) (11686.3206 4106.7023) (11689.6031 4112.3359) (11691.0687 4117.4198)
      (11690.0458 4120.8397) (11686.626 4121.8626) (11681.542 4120.3969) (11675.9084 4117.1145) (11670.8397 4113.2519)
      (11667.084 4110.3206) (11664.8397 4109.5878) (11663.771 4111.6947) (11663.1756 4116.4275) (11662.3206 4122.7328)
      (11660.6565 4129.0382) (11658.1069 4133.6794) (11654.9618 4135.374) (11651.8168 4133.6794) (11649.2672 4129.0382)
      (11647.6031 4122.7328) (11646.7481 4116.4275) (11646.1527 4111.6947) (11645.084 4109.5878) (11642.8397 4110.3206)
      (11639.084 4113.2519) (11634.0153 4117.1145) (11628.3817 4120.3969) (11623.2977 4121.8626) (11619.8779 4120.8397)
      (11618.855 4117.4198) (11620.3206 4112.3359) (11623.6031 4106.7023) (11627.4656 4101.6336) (11630.3969 4097.8779)
      (11631.1298 4095.6336) (11629.0229 4094.5649) (11624.2901 4093.9695) (11617.9695 4093.1145) (11611.6641 4091.4504)
      (11607.0382 4088.9008)
    ))
    ; P2883 -- see feature_dimensions_mm.csv
    ("06_ORNAMENT" 1 (
      (11633.5878 3007.6336) (11664.1221 2977.0992) (11694.6565 3007.6336) (11664.1221 3038.1679)
    ))
    ; P2884 -- see feature_dimensions_mm.csv
    ("06_ORNAMENT" 1 (
      (11633.5878 2916.0305) (11664.1221 2885.4962) (11694.6565 2916.0305) (11664.1221 2946.5649)
    ))
    ; P2885 -- see feature_dimensions_mm.csv
    ("06_ORNAMENT" 1 (
      (11636.6412 5409.4198) (11654.9618 5388.8092) (11673.2824 5409.4198) (11654.9618 5430.0305)
    ))
    ; P2886 -- see feature_dimensions_mm.csv
    ("06_ORNAMENT" 1 (
      (11636.6412 5097.9695) (11654.9618 5077.3588) (11673.2824 5097.9695) (11654.9618 5118.5802)
    ))
    ; P2887 -- see feature_dimensions_mm.csv
    ("06_ORNAMENT" 1 (
      (11636.6412 4786.5191) (11654.9618 4765.9084) (11673.2824 4786.5191) (11654.9618 4807.1298)
    ))
    ; P2888 -- see feature_dimensions_mm.csv
    ("06_ORNAMENT" 1 (
      (11636.6412 4163.6183) (11654.9618 4143.0076) (11673.2824 4163.6183) (11654.9618 4184.229)
    ))
    ; P2889 -- see feature_dimensions_mm.csv
    ("06_ORNAMENT" 1 (
      (11643.0534 5331.5573) (11643.9542 5326.9924) (11646.5344 5323.1298) (11650.4122 5320.5496) (11654.9618 5319.6489)
      (11659.5115 5320.5496) (11663.3893 5323.1298) (11665.9695 5326.9924) (11666.8702 5331.5573) (11665.9695 5336.1069)
      (11663.3893 5339.9695) (11659.5115 5342.5496) (11654.9618 5343.4656) (11650.4122 5342.5496) (11646.5344 5339.9695)
      (11643.9542 5336.1069)
    ))
    ; P2890 -- see feature_dimensions_mm.csv
    ("06_ORNAMENT" 1 (
      (11643.0534 5020.1069) (11643.9542 5015.542) (11646.5344 5011.6794) (11650.4122 5009.0992) (11654.9618 5008.1985)
      (11659.5115 5009.0992) (11663.3893 5011.6794) (11665.9695 5015.542) (11666.8702 5020.1069) (11665.9695 5024.6565)
      (11663.3893 5028.5191) (11659.5115 5031.0992) (11654.9618 5032.0153) (11650.4122 5031.0992) (11646.5344 5028.5191)
      (11643.9542 5024.6565)
    ))
    ; P2891 -- see feature_dimensions_mm.csv
    ("06_ORNAMENT" 1 (
      (11643.0534 4708.6565) (11643.9542 4704.0916) (11646.5344 4700.229) (11650.4122 4697.6489) (11654.9618 4696.7481)
      (11659.5115 4697.6489) (11663.3893 4700.229) (11665.9695 4704.0916) (11666.8702 4708.6565) (11665.9695 4713.2061)
      (11663.3893 4717.0687) (11659.5115 4719.6489) (11654.9618 4720.5649) (11650.4122 4719.6489) (11646.5344 4717.0687)
      (11643.9542 4713.2061)
    ))
    ; P2892 -- see feature_dimensions_mm.csv
    ("06_ORNAMENT" 1 (
      (11643.0534 4397.2061) (11643.9542 4392.6412) (11646.5344 4388.7786) (11650.4122 4386.1985) (11654.9618 4385.2977)
      (11659.5115 4386.1985) (11663.3893 4388.7786) (11665.9695 4392.6412) (11666.8702 4397.2061) (11665.9695 4401.7557)
      (11663.3893 4405.6183) (11659.5115 4408.1985) (11654.9618 4409.1145) (11650.4122 4408.1985) (11646.5344 4405.6183)
      (11643.9542 4401.7557)
    ))
    ; P2893 -- see feature_dimensions_mm.csv
    ("06_ORNAMENT" 1 (
      (11643.0534 4085.7557) (11643.9542 4081.1908) (11646.5344 4077.3282) (11650.4122 4074.7481) (11654.9618 4073.8473)
      (11659.5115 4074.7481) (11663.3893 4077.3282) (11665.9695 4081.1908) (11666.8702 4085.7557) (11665.9695 4090.3053)
      (11663.3893 4094.1679) (11659.5115 4096.7481) (11654.9618 4097.6641) (11650.4122 4096.7481) (11646.5344 4094.1679)
      (11643.9542 4090.3053)
    ))
    ; P2894 -- see feature_dimensions_mm.csv
    ("06_ORNAMENT" 1 (
      (11683.2061 5175.8321) (11684.9008 5172.687) (11689.5267 5170.1374) (11695.8321 5168.4733) (11702.1527 5167.6031)
      (11706.8855 5167.0229) (11708.9924 5165.9542) (11708.2595 5163.7099) (11705.3282 5159.9542) (11701.4656 5154.8855)
      (11698.1832 5149.2519) (11696.7176 5144.1679) (11697.7405 5140.7481) (11701.1603 5139.7252) (11706.2443 5141.1908)
      (11711.8779 5144.4733) (11716.9466 5148.3206) (11720.7023 5151.2519) (11722.9466 5151.9847) (11724.0153 5149.8931)
      (11724.6107 5145.1603) (11725.4656 5138.8397) (11727.1298 5132.5344) (11729.6794 5127.9084) (11732.8244 5126.2137)
      (11735.9695 5127.9084) (11738.5191 5132.5344) (11740.1832 5138.8397) (11741.0382 5145.1603) (11741.6336 5149.8931)
      (11742.7023 5151.9847) (11744.9466 5151.2519) (11748.7023 5148.3206) (11753.771 5144.4733) (11759.4046 5141.1908)
      (11764.4885 5139.7252) (11767.9084 5140.7481) (11768.9313 5144.1679) (11767.4656 5149.2519) (11764.1832 5154.8855)
      (11760.3206 5159.9542) (11757.3893 5163.7099) (11756.6565 5165.9542) (11758.7634 5167.0229) (11763.4962 5167.6031)
      (11769.8168 5168.4733) (11776.1221 5170.1374) (11780.7481 5172.687) (11782.4427 5175.8321) (11780.7481 5178.9771)
      (11776.1221 5181.5267) (11769.8168 5183.1908) (11763.4962 5184.0458) (11758.7634 5184.6412) (11756.6565 5185.7099)
      (11757.3893 5187.9542) (11760.3206 5191.7099) (11764.1832 5196.7786) (11767.4656 5202.4122) (11768.9313 5207.4962)
      (11767.9084 5210.916) (11764.4885 5211.9389) (11759.4046 5210.4733) (11753.771 5207.1908) (11748.7023 5203.3282)
      (11744.9466 5200.3969) (11742.7023 5199.6641) (11741.6336 5201.771) (11741.0382 5206.5038) (11740.1832 5212.8092)
      (11738.5191 5219.1145) (11735.9695 5223.7557) (11732.8244 5225.4504) (11729.6794 5223.7557) (11727.1298 5219.1145)
      (11725.4656 5212.8092) (11724.6107 5206.5038) (11724.0153 5201.771) (11722.9466 5199.6641) (11720.7023 5200.3969)
      (11716.9466 5203.3282) (11711.8779 5207.1908) (11706.2443 5210.4733) (11701.1603 5211.9389) (11697.7405 5210.916)
      (11696.7176 5207.4962) (11698.1832 5202.4122) (11701.4656 5196.7786) (11705.3282 5191.7099) (11708.2595 5187.9542)
      (11708.9924 5185.7099) (11706.8855 5184.6412) (11702.1527 5184.0458) (11695.8321 5183.1908) (11689.5267 5181.5267)
      (11684.9008 5178.9771)
    ))
    ; P2895 -- see feature_dimensions_mm.csv
    ("06_ORNAMENT" 1 (
      (11683.2061 4864.3817) (11684.9008 4861.2366) (11689.5267 4858.687) (11695.8321 4857.0229) (11702.1527 4856.1527)
      (11706.8855 4855.5725) (11708.9924 4854.5038) (11708.2595 4852.2595) (11705.3282 4848.5038) (11701.4656 4843.4351)
      (11698.1832 4837.8015) (11696.7176 4832.7176) (11697.7405 4829.2977) (11701.1603 4828.2748) (11706.2443 4829.7405)
      (11711.8779 4833.0229) (11716.9466 4836.8702) (11720.7023 4839.8015) (11722.9466 4840.5344) (11724.0153 4838.4427)
      (11724.6107 4833.7099) (11725.4656 4827.3893) (11727.1298 4821.084) (11729.6794 4816.458) (11732.8244 4814.7634)
      (11735.9695 4816.458) (11738.5191 4821.084) (11740.1832 4827.3893) (11741.0382 4833.7099) (11741.6336 4838.4427)
      (11742.7023 4840.5344) (11744.9466 4839.8015) (11748.7023 4836.8702) (11753.771 4833.0229) (11759.4046 4829.7405)
      (11764.4885 4828.2748) (11767.9084 4829.2977) (11768.9313 4832.7176) (11767.4656 4837.8015) (11764.1832 4843.4351)
      (11760.3206 4848.5038) (11757.3893 4852.2595) (11756.6565 4854.5038) (11758.7634 4855.5725) (11763.4962 4856.1527)
      (11769.8168 4857.0229) (11776.1221 4858.687) (11780.7481 4861.2366) (11782.4427 4864.3817) (11780.7481 4867.5267)
      (11776.1221 4870.0763) (11769.8168 4871.7405) (11763.4962 4872.5954) (11758.7634 4873.1908) (11756.6565 4874.2595)
      (11757.3893 4876.5038) (11760.3206 4880.2595) (11764.1832 4885.3282) (11767.4656 4890.9618) (11768.9313 4896.0458)
      (11767.9084 4899.4656) (11764.4885 4900.4885) (11759.4046 4899.0229) (11753.771 4895.7405) (11748.7023 4891.8779)
      (11744.9466 4888.9466) (11742.7023 4888.2137) (11741.6336 4890.3206) (11741.0382 4895.0534) (11740.1832 4901.3588)
      (11738.5191 4907.6641) (11735.9695 4912.3053) (11732.8244 4914.0) (11729.6794 4912.3053) (11727.1298 4907.6641)
      (11725.4656 4901.3588) (11724.6107 4895.0534) (11724.0153 4890.3206) (11722.9466 4888.2137) (11720.7023 4888.9466)
      (11716.9466 4891.8779) (11711.8779 4895.7405) (11706.2443 4899.0229) (11701.1603 4900.4885) (11697.7405 4899.4656)
      (11696.7176 4896.0458) (11698.1832 4890.9618) (11701.4656 4885.3282) (11705.3282 4880.2595) (11708.2595 4876.5038)
      (11708.9924 4874.2595) (11706.8855 4873.1908) (11702.1527 4872.5954) (11695.8321 4871.7405) (11689.5267 4870.0763)
      (11684.9008 4867.5267)
    ))
    ; P2896 -- see feature_dimensions_mm.csv
    ("06_ORNAMENT" 1 (
      (11683.2061 4552.9313) (11684.9008 4549.7863) (11689.5267 4547.2366) (11695.8321 4545.5725) (11702.1527 4544.7023)
      (11706.8855 4544.1221) (11708.9924 4543.0534) (11708.2595 4540.8092) (11705.3282 4537.0534) (11701.4656 4531.9847)
      (11698.1832 4526.3511) (11696.7176 4521.2672) (11697.7405 4517.8473) (11701.1603 4516.8244) (11706.2443 4518.2901)
      (11711.8779 4521.5725) (11716.9466 4525.4198) (11720.7023 4528.3511) (11722.9466 4529.084) (11724.0153 4526.9924)
      (11724.6107 4522.2595) (11725.4656 4515.9389) (11727.1298 4509.6336) (11729.6794 4505.0076) (11732.8244 4503.313)
      (11735.9695 4505.0076) (11738.5191 4509.6336) (11740.1832 4515.9389) (11741.0382 4522.2595) (11741.6336 4526.9924)
      (11742.7023 4529.084) (11744.9466 4528.3511) (11748.7023 4525.4198) (11753.771 4521.5725) (11759.4046 4518.2901)
      (11764.4885 4516.8244) (11767.9084 4517.8473) (11768.9313 4521.2672) (11767.4656 4526.3511) (11764.1832 4531.9847)
      (11760.3206 4537.0534) (11757.3893 4540.8092) (11756.6565 4543.0534) (11758.7634 4544.1221) (11763.4962 4544.7023)
      (11769.8168 4545.5725) (11776.1221 4547.2366) (11780.7481 4549.7863) (11782.4427 4552.9313) (11780.7481 4556.0763)
      (11776.1221 4558.626) (11769.8168 4560.2901) (11763.4962 4561.145) (11758.7634 4561.7405) (11756.6565 4562.8092)
      (11757.3893 4565.0534) (11760.3206 4568.8092) (11764.1832 4573.8779) (11767.4656 4579.5115) (11768.9313 4584.5954)
      (11767.9084 4588.0153) (11764.4885 4589.0382) (11759.4046 4587.5725) (11753.771 4584.2901) (11748.7023 4580.4275)
      (11744.9466 4577.4962) (11742.7023 4576.7634) (11741.6336 4578.8702) (11741.0382 4583.6031) (11740.1832 4589.9084)
      (11738.5191 4596.2137) (11735.9695 4600.855) (11732.8244 4602.5496) (11729.6794 4600.855) (11727.1298 4596.2137)
      (11725.4656 4589.9084) (11724.6107 4583.6031) (11724.0153 4578.8702) (11722.9466 4576.7634) (11720.7023 4577.4962)
      (11716.9466 4580.4275) (11711.8779 4584.2901) (11706.2443 4587.5725) (11701.1603 4589.0382) (11697.7405 4588.0153)
      (11696.7176 4584.5954) (11698.1832 4579.5115) (11701.4656 4573.8779) (11705.3282 4568.8092) (11708.2595 4565.0534)
      (11708.9924 4562.8092) (11706.8855 4561.7405) (11702.1527 4561.145) (11695.8321 4560.2901) (11689.5267 4558.626)
      (11684.9008 4556.0763)
    ))
    ; P2897 -- see feature_dimensions_mm.csv
    ("06_ORNAMENT" 1 (
      (11683.2061 4241.4809) (11684.9008 4238.3359) (11689.5267 4235.7863) (11695.8321 4234.1221) (11702.1527 4233.2519)
      (11706.8855 4232.6718) (11708.9924 4231.6031) (11708.2595 4229.3588) (11705.3282 4225.6031) (11701.4656 4220.5344)
      (11698.1832 4214.9008) (11696.7176 4209.8168) (11697.7405 4206.3969) (11701.1603 4205.374) (11706.2443 4206.8397)
      (11711.8779 4210.1221) (11716.9466 4213.9695) (11720.7023 4216.9008) (11722.9466 4217.6336) (11724.0153 4215.542)
      (11724.6107 4210.8092) (11725.4656 4204.4885) (11727.1298 4198.1832) (11729.6794 4193.5573) (11732.8244 4191.8626)
      (11735.9695 4193.5573) (11738.5191 4198.1832) (11740.1832 4204.4885) (11741.0382 4210.8092) (11741.6336 4215.542)
      (11742.7023 4217.6336) (11744.9466 4216.9008) (11748.7023 4213.9695) (11753.771 4210.1221) (11759.4046 4206.8397)
      (11764.4885 4205.374) (11767.9084 4206.3969) (11768.9313 4209.8168) (11767.4656 4214.9008) (11764.1832 4220.5344)
      (11760.3206 4225.6031) (11757.3893 4229.3588) (11756.6565 4231.6031) (11758.7634 4232.6718) (11763.4962 4233.2519)
      (11769.8168 4234.1221) (11776.1221 4235.7863) (11780.7481 4238.3359) (11782.4427 4241.4809) (11780.7481 4244.626)
      (11776.1221 4247.1756) (11769.8168 4248.8397) (11763.4962 4249.6947) (11758.7634 4250.2901) (11756.6565 4251.3588)
      (11757.3893 4253.6031) (11760.3206 4257.3588) (11764.1832 4262.4275) (11767.4656 4268.0611) (11768.9313 4273.145)
      (11767.9084 4276.5649) (11764.4885 4277.5878) (11759.4046 4276.1221) (11753.771 4272.8397) (11748.7023 4268.9771)
      (11744.9466 4266.0458) (11742.7023 4265.313) (11741.6336 4267.4198) (11741.0382 4272.1527) (11740.1832 4278.458)
      (11738.5191 4284.7634) (11735.9695 4289.4046) (11732.8244 4291.0992) (11729.6794 4289.4046) (11727.1298 4284.7634)
      (11725.4656 4278.458) (11724.6107 4272.1527) (11724.0153 4267.4198) (11722.9466 4265.313) (11720.7023 4266.0458)
      (11716.9466 4268.9771) (11711.8779 4272.8397) (11706.2443 4276.1221) (11701.1603 4277.5878) (11697.7405 4276.5649)
      (11696.7176 4273.145) (11698.1832 4268.0611) (11701.4656 4262.4275) (11705.3282 4257.3588) (11708.2595 4253.6031)
      (11708.9924 4251.3588) (11706.8855 4250.2901) (11702.1527 4249.6947) (11695.8321 4248.8397) (11689.5267 4247.1756)
      (11684.9008 4244.626)
    ))
    ; P2898 -- see feature_dimensions_mm.csv
    ("06_ORNAMENT" 1 (
      (11683.2061 3930.0305) (11684.9008 3926.8855) (11689.5267 3924.3359) (11695.8321 3922.6718) (11702.1527 3921.8015)
      (11706.8855 3921.2214) (11708.9924 3920.1527) (11708.2595 3917.9084) (11705.3282 3914.1527) (11701.4656 3909.084)
      (11698.1832 3903.4504) (11696.7176 3898.3664) (11697.7405 3894.9466) (11701.1603 3893.9237) (11706.2443 3895.3893)
      (11711.8779 3898.6718) (11716.9466 3902.5191) (11720.7023 3905.4504) (11722.9466 3906.1832) (11724.0153 3904.0916)
      (11724.6107 3899.3588) (11725.4656 3893.0382) (11727.1298 3886.7328) (11729.6794 3882.1069) (11732.8244 3880.4122)
      (11735.9695 3882.1069) (11738.5191 3886.7328) (11740.1832 3893.0382) (11741.0382 3899.3588) (11741.6336 3904.0916)
      (11742.7023 3906.1832) (11744.9466 3905.4504) (11748.7023 3902.5191) (11753.771 3898.6718) (11759.4046 3895.3893)
      (11764.4885 3893.9237) (11767.9084 3894.9466) (11768.9313 3898.3664) (11767.4656 3903.4504) (11764.1832 3909.084)
      (11760.3206 3914.1527) (11757.3893 3917.9084) (11756.6565 3920.1527) (11758.7634 3921.2214) (11763.4962 3921.8015)
      (11769.8168 3922.6718) (11776.1221 3924.3359) (11780.7481 3926.8855) (11782.4427 3930.0305) (11780.7481 3933.1756)
      (11776.1221 3935.7252) (11769.8168 3937.3893) (11763.4962 3938.2443) (11758.7634 3938.8397) (11756.6565 3939.9084)
      (11757.3893 3942.1527) (11760.3206 3945.9084) (11764.1832 3950.9771) (11767.4656 3956.6107) (11768.9313 3961.6947)
      (11767.9084 3965.1145) (11764.4885 3966.1374) (11759.4046 3964.6718) (11753.771 3961.3893) (11748.7023 3957.5267)
      (11744.9466 3954.5954) (11742.7023 3953.8626) (11741.6336 3955.9695) (11741.0382 3960.7023) (11740.1832 3967.0076)
      (11738.5191 3973.313) (11735.9695 3977.9542) (11732.8244 3979.6489) (11729.6794 3977.9542) (11727.1298 3973.313)
      (11725.4656 3967.0076) (11724.6107 3960.7023) (11724.0153 3955.9695) (11722.9466 3953.8626) (11720.7023 3954.5954)
      (11716.9466 3957.5267) (11711.8779 3961.3893) (11706.2443 3964.6718) (11701.1603 3966.1374) (11697.7405 3965.1145)
      (11696.7176 3961.6947) (11698.1832 3956.6107) (11701.4656 3950.9771) (11705.3282 3945.9084) (11708.2595 3942.1527)
      (11708.9924 3939.9084) (11706.8855 3938.8397) (11702.1527 3938.2443) (11695.8321 3937.3893) (11689.5267 3935.7252)
      (11684.9008 3933.1756)
    ))
    ; P2899 -- see feature_dimensions_mm.csv
    ("06_ORNAMENT" 1 (
      (11683.2061 1827.3893) (11694.6107 1822.1374) (11706.4275 1818.6107) (11718.5496 1816.687) (11730.8092 1816.2595)
      (11743.0687 1817.1908) (11755.2061 1819.3588) (11767.0687 1822.6565) (11778.5191 1826.9466) (11789.4046 1832.1221)
      (11799.6183 1838.0458) (11808.9771 1844.6107) (11816.5649 1851.0076) (11815.8473 1871.5725) (11810.0 1873.0076)
      (11798.6718 1874.7939) (11786.9008 1875.6947) (11774.8702 1875.6794) (11762.7328 1874.6718) (11750.7023 1872.6718)
      (11738.916 1869.6336) (11727.5573 1865.5115) (11716.7939 1860.2748) (11706.8092 1853.8779) (11697.771 1846.2901)
      (11689.8473 1837.4809)
    ))
    ; P2900 -- see feature_dimensions_mm.csv
    ("06_ORNAMENT" 1 (
      (11714.5038 5253.6947) (11732.8244 5233.084) (11751.145 5253.6947) (11732.8244 5274.3053)
    ))
    ; P2901 -- see feature_dimensions_mm.csv
    ("06_ORNAMENT" 1 (
      (11714.5038 4942.2443) (11732.8244 4921.6336) (11751.145 4942.2443) (11732.8244 4962.855)
    ))
    ; P2902 -- see feature_dimensions_mm.csv
    ("06_ORNAMENT" 1 (
      (11714.5038 4630.7939) (11732.8244 4610.1832) (11751.145 4630.7939) (11732.8244 4651.4046)
    ))
    ; P2903 -- see feature_dimensions_mm.csv
    ("06_ORNAMENT" 1 (
      (11714.5038 4319.3435) (11732.8244 4298.7328) (11751.145 4319.3435) (11732.8244 4339.9542)
    ))
    ; P2904 -- see feature_dimensions_mm.csv
    ("06_ORNAMENT" 1 (
      (11714.5038 4007.8931) (11732.8244 3987.2824) (11751.145 4007.8931) (11732.8244 4028.5038)
    ))
    ; P2905 -- see feature_dimensions_mm.csv
    ("06_ORNAMENT" 1 (
      (11720.916 5175.8321) (11721.8168 5171.2672) (11724.3969 5167.4046) (11728.2748 5164.8244) (11732.8244 5163.9237)
      (11737.374 5164.8244) (11741.2519 5167.4046) (11743.8321 5171.2672) (11744.7328 5175.8321) (11743.8321 5180.3817)
      (11741.2519 5184.2443) (11737.374 5186.8244) (11732.8244 5187.7405) (11728.2748 5186.8244) (11724.3969 5184.2443)
      (11721.8168 5180.3817)
    ))
    ; P2906 -- see feature_dimensions_mm.csv
    ("06_ORNAMENT" 1 (
      (11720.916 4864.3817) (11721.8168 4859.8168) (11724.3969 4855.9542) (11728.2748 4853.374) (11732.8244 4852.4733)
      (11737.374 4853.374) (11741.2519 4855.9542) (11743.8321 4859.8168) (11744.7328 4864.3817) (11743.8321 4868.9313)
      (11741.2519 4872.7939) (11737.374 4875.374) (11732.8244 4876.2901) (11728.2748 4875.374) (11724.3969 4872.7939)
      (11721.8168 4868.9313)
    ))
    ; P2907 -- see feature_dimensions_mm.csv
    ("06_ORNAMENT" 1 (
      (11720.916 4552.9313) (11721.8168 4548.3664) (11724.3969 4544.5038) (11728.2748 4541.9237) (11732.8244 4541.0229)
      (11737.374 4541.9237) (11741.2519 4544.5038) (11743.8321 4548.3664) (11744.7328 4552.9313) (11743.8321 4557.4809)
      (11741.2519 4561.3435) (11737.374 4563.9237) (11732.8244 4564.8397) (11728.2748 4563.9237) (11724.3969 4561.3435)
      (11721.8168 4557.4809)
    ))
    ; P2908 -- see feature_dimensions_mm.csv
    ("06_ORNAMENT" 1 (
      (11720.916 4241.4809) (11721.8168 4236.916) (11724.3969 4233.0534) (11728.2748 4230.4733) (11732.8244 4229.5725)
      (11737.374 4230.4733) (11741.2519 4233.0534) (11743.8321 4236.916) (11744.7328 4241.4809) (11743.8321 4246.0305)
      (11741.2519 4249.8931) (11737.374 4252.4733) (11732.8244 4253.3893) (11728.2748 4252.4733) (11724.3969 4249.8931)
      (11721.8168 4246.0305)
    ))
    ; P2909 -- see feature_dimensions_mm.csv
    ("06_ORNAMENT" 1 (
      (11720.916 3930.0305) (11721.8168 3925.4656) (11724.3969 3921.6031) (11728.2748 3919.0229) (11732.8244 3918.1221)
      (11737.374 3919.0229) (11741.2519 3921.6031) (11743.8321 3925.4656) (11744.7328 3930.0305) (11743.8321 3934.5802)
      (11741.2519 3938.4427) (11737.374 3941.0229) (11732.8244 3941.9389) (11728.2748 3941.0229) (11724.3969 3938.4427)
      (11721.8168 3934.5802)
    ))
    ; P2910 -- see feature_dimensions_mm.csv
    ("06_ORNAMENT" 1 (
      (11761.0687 5331.5573) (11762.7634 5328.4122) (11767.3893 5325.8626) (11773.6947 5324.1985) (11780.0153 5323.3282)
      (11784.7481 5322.7481) (11786.855 5321.6794) (11786.1221 5319.4351) (11783.1908 5315.6794) (11779.3282 5310.6107)
      (11776.0458 5304.9771) (11774.5802 5299.8931) (11775.6031 5296.4733) (11779.0229 5295.4504) (11784.1069 5296.916)
      (11789.7405 5300.1985) (11794.8092 5304.0458) (11798.5649 5306.9771) (11800.8092 5307.7099) (11801.8779 5305.6183)
      (11802.4733 5300.8855) (11803.3282 5294.5649) (11804.9924 5288.2595) (11807.542 5283.6336) (11810.687 5281.9389)
      (11813.8321 5283.6336) (11816.3817 5288.2595) (11818.0458 5294.5649) (11818.9008 5300.8855) (11819.4962 5305.6183)
      (11820.5649 5307.7099) (11822.8092 5306.9771) (11826.5649 5304.0458) (11831.6336 5300.1985) (11837.2672 5296.916)
      (11842.3511 5295.4504) (11845.771 5296.4733) (11846.7939 5299.8931) (11845.3282 5304.9771) (11842.0458 5310.6107)
      (11838.1832 5315.6794) (11835.2519 5319.4351) (11834.5191 5321.6794) (11836.626 5322.7481) (11841.3588 5323.3282)
      (11847.6794 5324.1985) (11853.9847 5325.8626) (11858.6107 5328.4122) (11860.3053 5331.5573) (11858.6107 5334.7023)
      (11853.9847 5337.2519) (11847.6794 5338.916) (11841.3588 5339.771) (11836.626 5340.3664) (11834.5191 5341.4351)
      (11835.2519 5343.6794) (11838.1832 5347.4351) (11842.0458 5352.5038) (11845.3282 5358.1374) (11846.7939 5363.2214)
      (11845.771 5366.6412) (11842.3511 5367.6641) (11837.2672 5366.1985) (11831.6336 5362.916) (11826.5649 5359.0534)
      (11822.8092 5356.1221) (11820.5649 5355.3893) (11819.4962 5357.4962) (11818.9008 5362.229) (11818.0458 5368.5344)
      (11816.3817 5374.8397) (11813.8321 5379.4809) (11810.687 5381.1756) (11807.542 5379.4809) (11804.9924 5374.8397)
      (11803.3282 5368.5344) (11802.4733 5362.229) (11801.8779 5357.4962) (11800.8092 5355.3893) (11798.5649 5356.1221)
      (11794.8092 5359.0534) (11789.7405 5362.916) (11784.1069 5366.1985) (11779.0229 5367.6641) (11775.6031 5366.6412)
      (11774.5802 5363.2214) (11776.0458 5358.1374) (11779.3282 5352.5038) (11783.1908 5347.4351) (11786.1221 5343.6794)
      (11786.855 5341.4351) (11784.7481 5340.3664) (11780.0153 5339.771) (11773.6947 5338.916) (11767.3893 5337.2519)
      (11762.7634 5334.7023)
    ))
    ; P2911 -- see feature_dimensions_mm.csv
    ("06_ORNAMENT" 1 (
      (11761.0687 5020.1069) (11762.7634 5016.9618) (11767.3893 5014.4122) (11773.6947 5012.7481) (11780.0153 5011.8779)
      (11784.7481 5011.2977) (11786.855 5010.229) (11786.1221 5007.9847) (11783.1908 5004.229) (11779.3282 4999.1603)
      (11776.0458 4993.5267) (11774.5802 4988.4427) (11775.6031 4985.0229) (11779.0229 4984.0) (11784.1069 4985.4656)
      (11789.7405 4988.7481) (11794.8092 4992.5954) (11798.5649 4995.5267) (11800.8092 4996.2595) (11801.8779 4994.1679)
      (11802.4733 4989.4351) (11803.3282 4983.1145) (11804.9924 4976.8092) (11807.542 4972.1832) (11810.687 4970.4885)
      (11813.8321 4972.1832) (11816.3817 4976.8092) (11818.0458 4983.1145) (11818.9008 4989.4351) (11819.4962 4994.1679)
      (11820.5649 4996.2595) (11822.8092 4995.5267) (11826.5649 4992.5954) (11831.6336 4988.7481) (11837.2672 4985.4656)
      (11842.3511 4984.0) (11845.771 4985.0229) (11846.7939 4988.4427) (11845.3282 4993.5267) (11842.0458 4999.1603)
      (11838.1832 5004.229) (11835.2519 5007.9847) (11834.5191 5010.229) (11836.626 5011.2977) (11841.3588 5011.8779)
      (11847.6794 5012.7481) (11853.9847 5014.4122) (11858.6107 5016.9618) (11860.3053 5020.1069) (11858.6107 5023.2519)
      (11853.9847 5025.8015) (11847.6794 5027.4656) (11841.3588 5028.3206) (11836.626 5028.916) (11834.5191 5029.9847)
      (11835.2519 5032.229) (11838.1832 5035.9847) (11842.0458 5041.0534) (11845.3282 5046.687) (11846.7939 5051.771)
      (11845.771 5055.1908) (11842.3511 5056.2137) (11837.2672 5054.7481) (11831.6336 5051.4656) (11826.5649 5047.6031)
      (11822.8092 5044.6718) (11820.5649 5043.9389) (11819.4962 5046.0458) (11818.9008 5050.7786) (11818.0458 5057.084)
      (11816.3817 5063.3893) (11813.8321 5068.0305) (11810.687 5069.7252) (11807.542 5068.0305) (11804.9924 5063.3893)
      (11803.3282 5057.084) (11802.4733 5050.7786) (11801.8779 5046.0458) (11800.8092 5043.9389) (11798.5649 5044.6718)
      (11794.8092 5047.6031) (11789.7405 5051.4656) (11784.1069 5054.7481) (11779.0229 5056.2137) (11775.6031 5055.1908)
      (11774.5802 5051.771) (11776.0458 5046.687) (11779.3282 5041.0534) (11783.1908 5035.9847) (11786.1221 5032.229)
      (11786.855 5029.9847) (11784.7481 5028.916) (11780.0153 5028.3206) (11773.6947 5027.4656) (11767.3893 5025.8015)
      (11762.7634 5023.2519)
    ))
    ; P2912 -- see feature_dimensions_mm.csv
    ("06_ORNAMENT" 1 (
      (11761.0687 4708.6565) (11762.7634 4705.5115) (11767.3893 4702.9618) (11773.6947 4701.2977) (11780.0153 4700.4275)
      (11784.7481 4699.8473) (11786.855 4698.7786) (11786.1221 4696.5344) (11783.1908 4692.7786) (11779.3282 4687.7099)
      (11776.0458 4682.0763) (11774.5802 4676.9924) (11775.6031 4673.5725) (11779.0229 4672.5496) (11784.1069 4674.0153)
      (11789.7405 4677.2977) (11794.8092 4681.145) (11798.5649 4684.0763) (11800.8092 4684.8092) (11801.8779 4682.7176)
      (11802.4733 4677.9847) (11803.3282 4671.6641) (11804.9924 4665.3588) (11807.542 4660.7328) (11810.687 4659.0382)
      (11813.8321 4660.7328) (11816.3817 4665.3588) (11818.0458 4671.6641) (11818.9008 4677.9847) (11819.4962 4682.7176)
      (11820.5649 4684.8092) (11822.8092 4684.0763) (11826.5649 4681.145) (11831.6336 4677.2977) (11837.2672 4674.0153)
      (11842.3511 4672.5496) (11845.771 4673.5725) (11846.7939 4676.9924) (11845.3282 4682.0763) (11842.0458 4687.7099)
      (11838.1832 4692.7786) (11835.2519 4696.5344) (11834.5191 4698.7786) (11836.626 4699.8473) (11841.3588 4700.4275)
      (11847.6794 4701.2977) (11853.9847 4702.9618) (11858.6107 4705.5115) (11860.3053 4708.6565) (11858.6107 4711.8015)
      (11853.9847 4714.3511) (11847.6794 4716.0153) (11841.3588 4716.8702) (11836.626 4717.4656) (11834.5191 4718.5344)
      (11835.2519 4720.7786) (11838.1832 4724.5344) (11842.0458 4729.6031) (11845.3282 4735.2366) (11846.7939 4740.3206)
      (11845.771 4743.7405) (11842.3511 4744.7634) (11837.2672 4743.2977) (11831.6336 4740.0153) (11826.5649 4736.1527)
      (11822.8092 4733.2214) (11820.5649 4732.4885) (11819.4962 4734.5954) (11818.9008 4739.3282) (11818.0458 4745.6336)
      (11816.3817 4751.9389) (11813.8321 4756.5802) (11810.687 4758.2748) (11807.542 4756.5802) (11804.9924 4751.9389)
      (11803.3282 4745.6336) (11802.4733 4739.3282) (11801.8779 4734.5954) (11800.8092 4732.4885) (11798.5649 4733.2214)
      (11794.8092 4736.1527) (11789.7405 4740.0153) (11784.1069 4743.2977) (11779.0229 4744.7634) (11775.6031 4743.7405)
      (11774.5802 4740.3206) (11776.0458 4735.2366) (11779.3282 4729.6031) (11783.1908 4724.5344) (11786.1221 4720.7786)
      (11786.855 4718.5344) (11784.7481 4717.4656) (11780.0153 4716.8702) (11773.6947 4716.0153) (11767.3893 4714.3511)
      (11762.7634 4711.8015)
    ))
    ; P2913 -- see feature_dimensions_mm.csv
    ("06_ORNAMENT" 1 (
      (11761.0687 4085.7557) (11762.7634 4082.6107) (11767.3893 4080.0611) (11773.6947 4078.3969) (11780.0153 4077.5267)
      (11784.7481 4076.9466) (11786.855 4075.8779) (11786.1221 4073.6336) (11783.1908 4069.8779) (11779.3282 4064.8092)
      (11776.0458 4059.1756) (11774.5802 4054.0916) (11775.6031 4050.6718) (11779.0229 4049.6489) (11784.1069 4051.1145)
      (11789.7405 4054.3969) (11794.8092 4058.2595) (11798.5649 4061.1756) (11800.8092 4061.9084) (11801.8779 4059.8168)
      (11802.4733 4055.084) (11803.3282 4048.7634) (11804.9924 4042.458) (11807.542 4037.8321) (11810.687 4036.1374)
      (11813.8321 4037.8321) (11816.3817 4042.458) (11818.0458 4048.7634) (11818.9008 4055.084) (11819.4962 4059.8168)
      (11820.5649 4061.9084) (11822.8092 4061.1756) (11826.5649 4058.2595) (11831.6336 4054.3969) (11837.2672 4051.1145)
      (11842.3511 4049.6489) (11845.771 4050.6718) (11846.7939 4054.0916) (11845.3282 4059.1756) (11842.0458 4064.8092)
      (11838.1832 4069.8779) (11835.2519 4073.6336) (11834.5191 4075.8779) (11836.626 4076.9466) (11841.3588 4077.5267)
      (11847.6794 4078.3969) (11853.9847 4080.0611) (11858.6107 4082.6107) (11860.3053 4085.7557) (11858.6107 4088.9008)
      (11853.9847 4091.4504) (11847.6794 4093.1145) (11841.3588 4093.9695) (11836.626 4094.5649) (11834.5191 4095.6336)
      (11835.2519 4097.8779) (11838.1832 4101.6336) (11842.0458 4106.7023) (11845.3282 4112.3359) (11846.7939 4117.4198)
      (11845.771 4120.8397) (11842.3511 4121.8626) (11837.2672 4120.3969) (11831.6336 4117.1145) (11826.5649 4113.2519)
      (11822.8092 4110.3206) (11820.5649 4109.5878) (11819.4962 4111.6947) (11818.9008 4116.4275) (11818.0458 4122.7328)
      (11816.3817 4129.0382) (11813.8321 4133.6794) (11810.687 4135.374) (11807.542 4133.6794) (11804.9924 4129.0382)
      (11803.3282 4122.7328) (11802.4733 4116.4275) (11801.8779 4111.6947) (11800.8092 4109.5878) (11798.5649 4110.3206)
      (11794.8092 4113.2519) (11789.7405 4117.1145) (11784.1069 4120.3969) (11779.0229 4121.8626) (11775.6031 4120.8397)
      (11774.5802 4117.4198) (11776.0458 4112.3359) (11779.3282 4106.7023) (11783.1908 4101.6336) (11786.1221 4097.8779)
      (11786.855 4095.6336) (11784.7481 4094.5649) (11780.0153 4093.9695) (11773.6947 4093.1145) (11767.3893 4091.4504)
      (11762.7634 4088.9008)
    ))
    ; P2914 -- see feature_dimensions_mm.csv
    ("06_ORNAMENT" 1 (
      (11762.9008 5874.4885) (11775.7557 5856.8244) (11790.8855 5841.0382) (11807.9695 5827.0992) (11826.6565 5814.9771)
      (11836.7786 5809.7252) (11845.0992 5811.4656) (11845.7557 5811.6031) (11892.7939 5820.7481) (11893.4046 5820.8702)
      (11931.9237 5827.8321) (11924.1832 5864.4122) (11910.0916 5870.3817) (11888.916 5877.4962) (11867.3893 5882.7939)
      (11845.771 5886.0458) (11824.2748 5887.0534) (11822.7176 5886.9466) (11826.7939 5888.3969) (11846.855 5898.0611)
      (11866.0763 5909.7557) (11884.2748 5923.1756) (11901.313 5938.0305) (11917.0382 5954.0) (11931.313 5970.8092)
      (11944.0 5988.1527) (11954.916 6005.7252) (11963.9237 6023.2366) (11969.7405 6037.542) (11971.4046 6037.0382)
      (11983.7863 6034.8397) (11994.458 6033.4809) (12002.1069 6031.9847) (12006.0611 6029.313) (12006.4122 6024.5496)
      (12003.8779 6017.1756) (11999.7099 6007.2672) (11995.4351 5995.4351) (11992.4733 5982.8397) (11991.9389 5970.9771)
      (11994.458 5961.374) (12000.0 5955.2977) (12008.0305 5953.5267) (12017.6183 5956.1679) (12027.6183 5962.5496)
      (12037.0382 5971.4046) (12045.145 5981.0229) (12051.6641 5989.5878) (12056.7634 5995.4656) (12061.0687 5997.5573)
      (12065.374 5995.4656) (12067.5115 5993.0076) (12064.5191 5991.0076) (12047.4962 5977.2824) (12032.229 5962.1221)
      (12019.0076 5945.5725) (12014.9924 5938.9313) (12139.8015 5938.9313) (12148.1527 5943.7099) (12166.7023 5956.3053)
      (12183.9847 5970.0153) (12199.7863 5984.5496) (12213.9389 5999.6489) (12226.1985 6015.084) (12236.3817 6030.5496)
      (12244.2748 6045.8015) (12225.7099 6046.1679) (12206.0611 6044.8702) (12185.6489 6041.8931) (12164.7634 6037.313)
      (12143.7405 6031.1298) (12122.9008 6023.374) (12117.0534 6020.7176) (12115.7252 6024.5496) (12116.0763 6029.313)
      (12120.0305 6031.9847) (12127.6794 6033.4809) (12138.3511 6034.8397) (12150.7328 6037.0382) (12163.1145 6040.7786)
      (12173.6489 6046.2443) (12180.7176 6053.2214) (12183.2061 6061.0687) (12180.7176 6068.916) (12173.6489 6075.8931)
      (12163.1145 6081.3588) (12150.7328 6085.0992) (12138.3511 6087.2977) (12127.6794 6088.6565) (12120.0305 6090.1527)
      (12116.0763 6092.8244) (12115.7252 6097.5878) (12118.2748 6104.9618) (12122.4275 6114.8702) (12126.7023 6126.7023)
      (12129.6641 6139.2977) (12130.1985 6151.1603) (12127.6794 6160.7634) (12122.1374 6166.8397) (12114.1069 6168.6107)
      (12104.5191 6165.9695) (12094.5191 6159.5878) (12085.0992 6150.7328) (12076.9924 6141.1145) (12070.4733 6132.5496)
      (12065.374 6126.6718) (12061.0687 6124.5802) (12056.7634 6126.6718) (12051.6641 6132.5496) (12045.145 6141.1145)
      (12037.0382 6150.7328) (12027.6183 6159.5878) (12017.6183 6165.9695) (12008.0305 6168.6107) (12000.0 6166.8397)
      (11994.458 6160.7634) (11991.9389 6151.1603) (11992.4733 6139.2977) (11995.4351 6126.7023) (11999.7099 6114.8702)
      (12003.8779 6104.9618) (12006.4122 6097.5878) (12006.0611 6092.8244) (12002.1069 6090.1527) (11994.458 6088.6565)
      (11983.7863 6087.2977) (11971.4046 6085.0992) (11959.0229 6081.3588) (11948.4885 6075.8931) (11941.4198 6068.916)
      (11938.9313 6061.0687) (11941.4198 6053.2214) (11944.5038 6050.1832) (11938.3817 6048.5191) (11918.9313 6041.6336)
      (11899.3435 6033.0687) (11879.9389 6022.9008) (11861.0076 6011.2366) (11842.8397 5998.1527) (11825.7557 5983.7405)
      (11810.0611 5968.0916) (11796.0458 5951.313) (11784.0153 5933.4656) (11774.2901 5914.6565) (11767.145 5894.9618)
    ))
    ; P2915 -- see feature_dimensions_mm.csv
    ("06_ORNAMENT" 1 (
      (11792.3664 5409.4198) (11810.687 5388.8092) (11829.0076 5409.4198) (11810.687 5430.0305)
    ))
    ; P2916 -- see feature_dimensions_mm.csv
    ("06_ORNAMENT" 1 (
      (11792.3664 5097.9695) (11810.687 5077.3588) (11829.0076 5097.9695) (11810.687 5118.5802)
    ))
    ; P2917 -- see feature_dimensions_mm.csv
    ("06_ORNAMENT" 1 (
      (11792.3664 4786.5191) (11810.687 4765.9084) (11829.0076 4786.5191) (11810.687 4807.1298)
    ))
    ; P2918 -- see feature_dimensions_mm.csv
    ("06_ORNAMENT" 1 (
      (11792.3664 4163.6183) (11810.687 4143.0076) (11829.0076 4163.6183) (11810.687 4184.229)
    ))
    ; P2919 -- see feature_dimensions_mm.csv
    ("06_ORNAMENT" 1 (
      (11798.7786 5331.5573) (11799.6794 5326.9924) (11802.2595 5323.1298) (11806.1374 5320.5496) (11810.687 5319.6489)
      (11815.2366 5320.5496) (11819.1145 5323.1298) (11821.6947 5326.9924) (11822.5954 5331.5573) (11821.6947 5336.1069)
      (11819.1145 5339.9695) (11815.2366 5342.5496) (11810.687 5343.4656) (11806.1374 5342.5496) (11802.2595 5339.9695)
      (11799.6794 5336.1069)
    ))
    ; P2920 -- see feature_dimensions_mm.csv
    ("06_ORNAMENT" 1 (
      (11798.7786 5020.1069) (11799.6794 5015.542) (11802.2595 5011.6794) (11806.1374 5009.0992) (11810.687 5008.1985)
      (11815.2366 5009.0992) (11819.1145 5011.6794) (11821.6947 5015.542) (11822.5954 5020.1069) (11821.6947 5024.6565)
      (11819.1145 5028.5191) (11815.2366 5031.0992) (11810.687 5032.0153) (11806.1374 5031.0992) (11802.2595 5028.5191)
      (11799.6794 5024.6565)
    ))
    ; P2921 -- see feature_dimensions_mm.csv
    ("06_ORNAMENT" 1 (
      (11798.7786 4708.6565) (11799.6794 4704.0916) (11802.2595 4700.229) (11806.1374 4697.6489) (11810.687 4696.7481)
      (11815.2366 4697.6489) (11819.1145 4700.229) (11821.6947 4704.0916) (11822.5954 4708.6565) (11821.6947 4713.2061)
      (11819.1145 4717.0687) (11815.2366 4719.6489) (11810.687 4720.5649) (11806.1374 4719.6489) (11802.2595 4717.0687)
      (11799.6794 4713.2061)
    ))
    ; P2922 -- see feature_dimensions_mm.csv
    ("06_ORNAMENT" 1 (
      (11798.7786 4397.2061) (11799.6794 4392.6412) (11802.2595 4388.7786) (11806.1374 4386.1985) (11810.687 4385.2977)
      (11815.2366 4386.1985) (11819.1145 4388.7786) (11821.6947 4392.6412) (11822.5954 4397.2061) (11821.6947 4401.7557)
      (11819.1145 4405.6183) (11815.2366 4408.1985) (11810.687 4409.1145) (11806.1374 4408.1985) (11802.2595 4405.6183)
      (11799.6794 4401.7557)
    ))
    ; P2923 -- see feature_dimensions_mm.csv
    ("06_ORNAMENT" 1 (
      (11798.7786 4085.7557) (11799.6794 4081.1908) (11802.2595 4077.3282) (11806.1374 4074.7481) (11810.687 4073.8473)
      (11815.2366 4074.7481) (11819.1145 4077.3282) (11821.6947 4081.1908) (11822.5954 4085.7557) (11821.6947 4090.3053)
      (11819.1145 4094.1679) (11815.2366 4096.7481) (11810.687 4097.6641) (11806.1374 4096.7481) (11802.2595 4094.1679)
      (11799.6794 4090.3053)
    ))
    ; P2924 -- see feature_dimensions_mm.csv
    ("06_ORNAMENT" 1 (
      (11838.9313 5487.2824) (11840.626 5484.1374) (11845.2519 5481.5878) (11851.5573 5479.9237) (11857.8779 5479.0534)
      (11862.6107 5478.4733) (11864.7176 5477.4046) (11863.9847 5475.1603) (11861.0534 5471.4046) (11857.1908 5466.3359)
      (11853.9084 5460.7023) (11852.4427 5455.6183) (11853.4656 5452.1985) (11856.8855 5451.1756) (11861.9695 5452.6412)
      (11867.6031 5455.9237) (11872.6718 5459.771) (11876.4275 5462.7023) (11878.6718 5463.4351) (11879.7405 5461.3435)
      (11880.3359 5456.6107) (11881.1908 5450.2901) (11882.855 5443.9847) (11885.4046 5439.3588) (11888.5496 5437.6641)
      (11891.6947 5439.3588) (11894.2443 5443.9847) (11895.9084 5450.2901) (11896.7634 5456.6107) (11897.3588 5461.3435)
      (11898.4275 5463.4351) (11900.6718 5462.7023) (11904.4275 5459.771) (11909.4962 5455.9237) (11915.1298 5452.6412)
      (11920.2137 5451.1756) (11923.6336 5452.1985) (11924.6565 5455.6183) (11923.1908 5460.7023) (11919.9084 5466.3359)
      (11916.0458 5471.4046) (11913.1145 5475.1603) (11912.3817 5477.4046) (11914.4885 5478.4733) (11919.2214 5479.0534)
      (11925.542 5479.9237) (11931.8473 5481.5878) (11936.4733 5484.1374) (11938.1679 5487.2824) (11936.4733 5490.4275)
      (11931.8473 5492.9771) (11925.542 5494.6412) (11919.2214 5495.4962) (11914.4885 5496.0916) (11912.3817 5497.1603)
      (11913.1145 5499.4046) (11916.0458 5503.1603) (11919.9084 5508.229) (11923.1908 5513.8626) (11924.6565 5518.9466)
      (11923.6336 5522.3664) (11920.2137 5523.3893) (11915.1298 5521.9237) (11909.4962 5518.6412) (11904.4275 5514.7786)
      (11900.6718 5511.8473) (11898.4275 5511.1145) (11897.3588 5513.2214) (11896.7634 5517.9542) (11895.9084 5524.2595)
      (11894.2443 5530.5649) (11891.6947 5535.2061) (11888.5496 5536.9008) (11885.4046 5535.2061) (11882.855 5530.5649)
      (11881.1908 5524.2595) (11880.3359 5517.9542) (11879.7405 5513.2214) (11878.6718 5511.1145) (11876.4275 5511.8473)
      (11872.6718 5514.7786) (11867.6031 5518.6412) (11861.9695 5521.9237) (11856.8855 5523.3893) (11853.4656 5522.3664)
      (11852.4427 5518.9466) (11853.9084 5513.8626) (11857.1908 5508.229) (11861.0534 5503.1603) (11863.9847 5499.4046)
      (11864.7176 5497.1603) (11862.6107 5496.0916) (11857.8779 5495.4962) (11851.5573 5494.6412) (11845.2519 5492.9771)
      (11840.626 5490.4275)
    ))
    ; P2925 -- see feature_dimensions_mm.csv
    ("06_ORNAMENT" 1 (
      (11838.9313 5175.8321) (11840.626 5172.687) (11845.2519 5170.1374) (11851.5573 5168.4733) (11857.8779 5167.6031)
      (11862.6107 5167.0229) (11864.7176 5165.9542) (11863.9847 5163.7099) (11861.0534 5159.9542) (11857.1908 5154.8855)
      (11853.9084 5149.2519) (11852.4427 5144.1679) (11853.4656 5140.7481) (11856.8855 5139.7252) (11861.9695 5141.1908)
      (11867.6031 5144.4733) (11872.6718 5148.3206) (11876.4275 5151.2519) (11878.6718 5151.9847) (11879.7405 5149.8931)
      (11880.3359 5145.1603) (11881.1908 5138.8397) (11882.855 5132.5344) (11885.4046 5127.9084) (11888.5496 5126.2137)
      (11891.6947 5127.9084) (11894.2443 5132.5344) (11895.9084 5138.8397) (11896.7634 5145.1603) (11897.3588 5149.8931)
      (11898.4275 5151.9847) (11900.6718 5151.2519) (11904.4275 5148.3206) (11909.4962 5144.4733) (11915.1298 5141.1908)
      (11920.2137 5139.7252) (11923.6336 5140.7481) (11924.6565 5144.1679) (11923.1908 5149.2519) (11919.9084 5154.8855)
      (11916.0458 5159.9542) (11913.1145 5163.7099) (11912.3817 5165.9542) (11914.4885 5167.0229) (11919.2214 5167.6031)
      (11925.542 5168.4733) (11931.8473 5170.1374) (11936.4733 5172.687) (11938.1679 5175.8321) (11936.4733 5178.9771)
      (11931.8473 5181.5267) (11925.542 5183.1908) (11919.2214 5184.0458) (11914.4885 5184.6412) (11912.3817 5185.7099)
      (11913.1145 5187.9542) (11916.0458 5191.7099) (11919.9084 5196.7786) (11923.1908 5202.4122) (11924.6565 5207.4962)
      (11923.6336 5210.916) (11920.2137 5211.9389) (11915.1298 5210.4733) (11909.4962 5207.1908) (11904.4275 5203.3282)
      (11900.6718 5200.3969) (11898.4275 5199.6641) (11897.3588 5201.771) (11896.7634 5206.5038) (11895.9084 5212.8092)
      (11894.2443 5219.1145) (11891.6947 5223.7557) (11888.5496 5225.4504) (11885.4046 5223.7557) (11882.855 5219.1145)
      (11881.1908 5212.8092) (11880.3359 5206.5038) (11879.7405 5201.771) (11878.6718 5199.6641) (11876.4275 5200.3969)
      (11872.6718 5203.3282) (11867.6031 5207.1908) (11861.9695 5210.4733) (11856.8855 5211.9389) (11853.4656 5210.916)
      (11852.4427 5207.4962) (11853.9084 5202.4122) (11857.1908 5196.7786) (11861.0534 5191.7099) (11863.9847 5187.9542)
      (11864.7176 5185.7099) (11862.6107 5184.6412) (11857.8779 5184.0458) (11851.5573 5183.1908) (11845.2519 5181.5267)
      (11840.626 5178.9771)
    ))
    ; P2926 -- see feature_dimensions_mm.csv
    ("06_ORNAMENT" 1 (
      (11838.9313 4864.3817) (11840.626 4861.2366) (11845.2519 4858.687) (11851.5573 4857.0229) (11857.8779 4856.1527)
      (11862.6107 4855.5725) (11864.7176 4854.5038) (11863.9847 4852.2595) (11861.0534 4848.5038) (11857.1908 4843.4351)
      (11853.9084 4837.8015) (11852.4427 4832.7176) (11853.4656 4829.2977) (11856.8855 4828.2748) (11861.9695 4829.7405)
      (11867.6031 4833.0229) (11872.6718 4836.8702) (11876.4275 4839.8015) (11878.6718 4840.5344) (11879.7405 4838.4427)
      (11880.3359 4833.7099) (11881.1908 4827.3893) (11882.855 4821.084) (11885.4046 4816.458) (11888.5496 4814.7634)
      (11891.6947 4816.458) (11894.2443 4821.084) (11895.9084 4827.3893) (11896.7634 4833.7099) (11897.3588 4838.4427)
      (11898.4275 4840.5344) (11900.6718 4839.8015) (11904.4275 4836.8702) (11909.4962 4833.0229) (11915.1298 4829.7405)
      (11920.2137 4828.2748) (11923.6336 4829.2977) (11924.6565 4832.7176) (11923.1908 4837.8015) (11919.9084 4843.4351)
      (11916.0458 4848.5038) (11913.1145 4852.2595) (11912.3817 4854.5038) (11914.4885 4855.5725) (11919.2214 4856.1527)
      (11925.542 4857.0229) (11931.8473 4858.687) (11936.4733 4861.2366) (11938.1679 4864.3817) (11936.4733 4867.5267)
      (11931.8473 4870.0763) (11925.542 4871.7405) (11919.2214 4872.5954) (11914.4885 4873.1908) (11912.3817 4874.2595)
      (11913.1145 4876.5038) (11916.0458 4880.2595) (11919.9084 4885.3282) (11923.1908 4890.9618) (11924.6565 4896.0458)
      (11923.6336 4899.4656) (11920.2137 4900.4885) (11915.1298 4899.0229) (11909.4962 4895.7405) (11904.4275 4891.8779)
      (11900.6718 4888.9466) (11898.4275 4888.2137) (11897.3588 4890.3206) (11896.7634 4895.0534) (11895.9084 4901.3588)
      (11894.2443 4907.6641) (11891.6947 4912.3053) (11888.5496 4914.0) (11885.4046 4912.3053) (11882.855 4907.6641)
      (11881.1908 4901.3588) (11880.3359 4895.0534) (11879.7405 4890.3206) (11878.6718 4888.2137) (11876.4275 4888.9466)
      (11872.6718 4891.8779) (11867.6031 4895.7405) (11861.9695 4899.0229) (11856.8855 4900.4885) (11853.4656 4899.4656)
      (11852.4427 4896.0458) (11853.9084 4890.9618) (11857.1908 4885.3282) (11861.0534 4880.2595) (11863.9847 4876.5038)
      (11864.7176 4874.2595) (11862.6107 4873.1908) (11857.8779 4872.5954) (11851.5573 4871.7405) (11845.2519 4870.0763)
      (11840.626 4867.5267)
    ))
    ; P2927 -- see feature_dimensions_mm.csv
    ("06_ORNAMENT" 1 (
      (11838.9313 4552.9313) (11840.626 4549.7863) (11845.2519 4547.2366) (11851.5573 4545.5725) (11857.8779 4544.7023)
      (11862.6107 4544.1221) (11864.7176 4543.0534) (11863.9847 4540.8092) (11861.0534 4537.0534) (11857.1908 4531.9847)
      (11853.9084 4526.3511) (11852.4427 4521.2672) (11853.4656 4517.8473) (11856.8855 4516.8244) (11861.9695 4518.2901)
      (11867.6031 4521.5725) (11872.6718 4525.4198) (11876.4275 4528.3511) (11878.6718 4529.084) (11879.7405 4526.9924)
      (11880.3359 4522.2595) (11881.1908 4515.9389) (11882.855 4509.6336) (11885.4046 4505.0076) (11888.5496 4503.313)
      (11891.6947 4505.0076) (11894.2443 4509.6336) (11895.9084 4515.9389) (11896.7634 4522.2595) (11897.3588 4526.9924)
      (11898.4275 4529.084) (11900.6718 4528.3511) (11904.4275 4525.4198) (11909.4962 4521.5725) (11915.1298 4518.2901)
      (11920.2137 4516.8244) (11923.6336 4517.8473) (11924.6565 4521.2672) (11923.1908 4526.3511) (11919.9084 4531.9847)
      (11916.0458 4537.0534) (11913.1145 4540.8092) (11912.3817 4543.0534) (11914.4885 4544.1221) (11919.2214 4544.7023)
      (11925.542 4545.5725) (11931.8473 4547.2366) (11936.4733 4549.7863) (11938.1679 4552.9313) (11936.4733 4556.0763)
      (11931.8473 4558.626) (11925.542 4560.2901) (11919.2214 4561.145) (11914.4885 4561.7405) (11912.3817 4562.8092)
      (11913.1145 4565.0534) (11916.0458 4568.8092) (11919.9084 4573.8779) (11923.1908 4579.5115) (11924.6565 4584.5954)
      (11923.6336 4588.0153) (11920.2137 4589.0382) (11915.1298 4587.5725) (11909.4962 4584.2901) (11904.4275 4580.4275)
      (11900.6718 4577.4962) (11898.4275 4576.7634) (11897.3588 4578.8702) (11896.7634 4583.6031) (11895.9084 4589.9084)
      (11894.2443 4596.2137) (11891.6947 4600.855) (11888.5496 4602.5496) (11885.4046 4600.855) (11882.855 4596.2137)
      (11881.1908 4589.9084) (11880.3359 4583.6031) (11879.7405 4578.8702) (11878.6718 4576.7634) (11876.4275 4577.4962)
      (11872.6718 4580.4275) (11867.6031 4584.2901) (11861.9695 4587.5725) (11856.8855 4589.0382) (11853.4656 4588.0153)
      (11852.4427 4584.5954) (11853.9084 4579.5115) (11857.1908 4573.8779) (11861.0534 4568.8092) (11863.9847 4565.0534)
      (11864.7176 4562.8092) (11862.6107 4561.7405) (11857.8779 4561.145) (11851.5573 4560.2901) (11845.2519 4558.626)
      (11840.626 4556.0763)
    ))
    ; P2928 -- see feature_dimensions_mm.csv
    ("06_ORNAMENT" 1 (
      (11838.9313 4241.4809) (11840.626 4238.3359) (11845.2519 4235.7863) (11851.5573 4234.1221) (11857.8779 4233.2519)
      (11862.6107 4232.6718) (11864.7176 4231.6031) (11863.9847 4229.3588) (11861.0534 4225.6031) (11857.1908 4220.5344)
      (11853.9084 4214.9008) (11852.4427 4209.8168) (11853.4656 4206.3969) (11856.8855 4205.374) (11861.9695 4206.8397)
      (11867.6031 4210.1221) (11872.6718 4213.9695) (11876.4275 4216.9008) (11878.6718 4217.6336) (11879.7405 4215.542)
      (11880.3359 4210.8092) (11881.1908 4204.4885) (11882.855 4198.1832) (11885.4046 4193.5573) (11888.5496 4191.8626)
      (11891.6947 4193.5573) (11894.2443 4198.1832) (11895.9084 4204.4885) (11896.7634 4210.8092) (11897.3588 4215.542)
      (11898.4275 4217.6336) (11900.6718 4216.9008) (11904.4275 4213.9695) (11909.4962 4210.1221) (11915.1298 4206.8397)
      (11920.2137 4205.374) (11923.6336 4206.3969) (11924.6565 4209.8168) (11923.1908 4214.9008) (11919.9084 4220.5344)
      (11916.0458 4225.6031) (11913.1145 4229.3588) (11912.3817 4231.6031) (11914.4885 4232.6718) (11919.2214 4233.2519)
      (11925.542 4234.1221) (11931.8473 4235.7863) (11936.4733 4238.3359) (11938.1679 4241.4809) (11936.4733 4244.626)
      (11931.8473 4247.1756) (11925.542 4248.8397) (11919.2214 4249.6947) (11914.4885 4250.2901) (11912.3817 4251.3588)
      (11913.1145 4253.6031) (11916.0458 4257.3588) (11919.9084 4262.4275) (11923.1908 4268.0611) (11924.6565 4273.145)
      (11923.6336 4276.5649) (11920.2137 4277.5878) (11915.1298 4276.1221) (11909.4962 4272.8397) (11904.4275 4268.9771)
      (11900.6718 4266.0458) (11898.4275 4265.313) (11897.3588 4267.4198) (11896.7634 4272.1527) (11895.9084 4278.458)
      (11894.2443 4284.7634) (11891.6947 4289.4046) (11888.5496 4291.0992) (11885.4046 4289.4046) (11882.855 4284.7634)
      (11881.1908 4278.458) (11880.3359 4272.1527) (11879.7405 4267.4198) (11878.6718 4265.313) (11876.4275 4266.0458)
      (11872.6718 4268.9771) (11867.6031 4272.8397) (11861.9695 4276.1221) (11856.8855 4277.5878) (11853.4656 4276.5649)
      (11852.4427 4273.145) (11853.9084 4268.0611) (11857.1908 4262.4275) (11861.0534 4257.3588) (11863.9847 4253.6031)
      (11864.7176 4251.3588) (11862.6107 4250.2901) (11857.8779 4249.6947) (11851.5573 4248.8397) (11845.2519 4247.1756)
      (11840.626 4244.626)
    ))
    ; P2929 -- see feature_dimensions_mm.csv
    ("06_ORNAMENT" 1 (
      (11838.9313 3930.0305) (11840.626 3926.8855) (11845.2519 3924.3359) (11851.5573 3922.6718) (11857.8779 3921.8015)
      (11862.6107 3921.2214) (11864.7176 3920.1527) (11863.9847 3917.9084) (11861.0534 3914.1527) (11857.1908 3909.084)
      (11853.9084 3903.4504) (11852.4427 3898.3664) (11853.4656 3894.9466) (11856.8855 3893.9237) (11861.9695 3895.3893)
      (11867.6031 3898.6718) (11872.6718 3902.5191) (11876.4275 3905.4504) (11878.6718 3906.1832) (11879.7405 3904.0916)
      (11880.3359 3899.3588) (11881.1908 3893.0382) (11882.855 3886.7328) (11885.4046 3882.1069) (11888.5496 3880.4122)
      (11891.6947 3882.1069) (11894.2443 3886.7328) (11895.9084 3893.0382) (11896.7634 3899.3588) (11897.3588 3904.0916)
      (11898.4275 3906.1832) (11900.6718 3905.4504) (11904.4275 3902.5191) (11909.4962 3898.6718) (11915.1298 3895.3893)
      (11920.2137 3893.9237) (11923.6336 3894.9466) (11924.6565 3898.3664) (11923.1908 3903.4504) (11919.9084 3909.084)
      (11916.0458 3914.1527) (11913.1145 3917.9084) (11912.3817 3920.1527) (11914.4885 3921.2214) (11919.2214 3921.8015)
      (11925.542 3922.6718) (11931.8473 3924.3359) (11936.4733 3926.8855) (11938.1679 3930.0305) (11936.4733 3933.1756)
      (11931.8473 3935.7252) (11925.542 3937.3893) (11919.2214 3938.2443) (11914.4885 3938.8397) (11912.3817 3939.9084)
      (11913.1145 3942.1527) (11916.0458 3945.9084) (11919.9084 3950.9771) (11923.1908 3956.6107) (11924.6565 3961.6947)
      (11923.6336 3965.1145) (11920.2137 3966.1374) (11915.1298 3964.6718) (11909.4962 3961.3893) (11904.4275 3957.5267)
      (11900.6718 3954.5954) (11898.4275 3953.8626) (11897.3588 3955.9695) (11896.7634 3960.7023) (11895.9084 3967.0076)
      (11894.2443 3973.313) (11891.6947 3977.9542) (11888.5496 3979.6489) (11885.4046 3977.9542) (11882.855 3973.313)
      (11881.1908 3967.0076) (11880.3359 3960.7023) (11879.7405 3955.9695) (11878.6718 3953.8626) (11876.4275 3954.5954)
      (11872.6718 3957.5267) (11867.6031 3961.3893) (11861.9695 3964.6718) (11856.8855 3966.1374) (11853.4656 3965.1145)
      (11852.4427 3961.6947) (11853.9084 3956.6107) (11857.1908 3950.9771) (11861.0534 3945.9084) (11863.9847 3942.1527)
      (11864.7176 3939.9084) (11862.6107 3938.8397) (11857.8779 3938.2443) (11851.5573 3937.3893) (11845.2519 3935.7252)
      (11840.626 3933.1756)
    ))
    ; P2930 -- see feature_dimensions_mm.csv
    ("06_ORNAMENT" 1 (
      (11870.229 5253.6947) (11888.5496 5233.084) (11906.8702 5253.6947) (11888.5496 5274.3053)
    ))
    ; P2931 -- see feature_dimensions_mm.csv
    ("06_ORNAMENT" 1 (
      (11870.229 4942.2443) (11888.5496 4921.6336) (11906.8702 4942.2443) (11888.5496 4962.855)
    ))
    ; P2932 -- see feature_dimensions_mm.csv
    ("06_ORNAMENT" 1 (
      (11870.229 4630.7939) (11888.5496 4610.1832) (11906.8702 4630.7939) (11888.5496 4651.4046)
    ))
    ; P2933 -- see feature_dimensions_mm.csv
    ("06_ORNAMENT" 1 (
      (11870.229 4319.3435) (11888.5496 4298.7328) (11906.8702 4319.3435) (11888.5496 4339.9542)
    ))
    ; P2934 -- see feature_dimensions_mm.csv
    ("06_ORNAMENT" 1 (
      (11870.229 4007.8931) (11888.5496 3987.2824) (11906.8702 4007.8931) (11888.5496 4028.5038)
    ))
    ; P2935 -- see feature_dimensions_mm.csv
    ("06_ORNAMENT" 1 (
      (11876.6412 5487.2824) (11877.542 5482.7176) (11880.1221 5478.855) (11884.0 5476.2748) (11888.5496 5475.374)
      (11893.0992 5476.2748) (11896.9771 5478.855) (11899.5573 5482.7176) (11900.458 5487.2824) (11899.5573 5491.8321)
      (11896.9771 5495.6947) (11893.0992 5498.2748) (11888.5496 5499.1908) (11884.0 5498.2748) (11880.1221 5495.6947)
      (11877.542 5491.8321)
    ))
    ; P2936 -- see feature_dimensions_mm.csv
    ("06_ORNAMENT" 1 (
      (11876.6412 5175.8321) (11877.542 5171.2672) (11880.1221 5167.4046) (11884.0 5164.8244) (11888.5496 5163.9237)
      (11893.0992 5164.8244) (11896.9771 5167.4046) (11899.5573 5171.2672) (11900.458 5175.8321) (11899.5573 5180.3817)
      (11896.9771 5184.2443) (11893.0992 5186.8244) (11888.5496 5187.7405) (11884.0 5186.8244) (11880.1221 5184.2443)
      (11877.542 5180.3817)
    ))
    ; P2937 -- see feature_dimensions_mm.csv
    ("06_ORNAMENT" 1 (
      (11876.6412 4864.3817) (11877.542 4859.8168) (11880.1221 4855.9542) (11884.0 4853.374) (11888.5496 4852.4733)
      (11893.0992 4853.374) (11896.9771 4855.9542) (11899.5573 4859.8168) (11900.458 4864.3817) (11899.5573 4868.9313)
      (11896.9771 4872.7939) (11893.0992 4875.374) (11888.5496 4876.2901) (11884.0 4875.374) (11880.1221 4872.7939)
      (11877.542 4868.9313)
    ))
    ; P2938 -- see feature_dimensions_mm.csv
    ("06_ORNAMENT" 1 (
      (11876.6412 4552.9313) (11877.542 4548.3664) (11880.1221 4544.5038) (11884.0 4541.9237) (11888.5496 4541.0229)
      (11893.0992 4541.9237) (11896.9771 4544.5038) (11899.5573 4548.3664) (11900.458 4552.9313) (11899.5573 4557.4809)
      (11896.9771 4561.3435) (11893.0992 4563.9237) (11888.5496 4564.8397) (11884.0 4563.9237) (11880.1221 4561.3435)
      (11877.542 4557.4809)
    ))
    ; P2939 -- see feature_dimensions_mm.csv
    ("06_ORNAMENT" 1 (
      (11876.6412 4241.4809) (11877.542 4236.916) (11880.1221 4233.0534) (11884.0 4230.4733) (11888.5496 4229.5725)
      (11893.0992 4230.4733) (11896.9771 4233.0534) (11899.5573 4236.916) (11900.458 4241.4809) (11899.5573 4246.0305)
      (11896.9771 4249.8931) (11893.0992 4252.4733) (11888.5496 4253.3893) (11884.0 4252.4733) (11880.1221 4249.8931)
      (11877.542 4246.0305)
    ))
    ; P2940 -- see feature_dimensions_mm.csv
    ("06_ORNAMENT" 1 (
      (11876.6412 3930.0305) (11877.542 3925.4656) (11880.1221 3921.6031) (11884.0 3919.0229) (11888.5496 3918.1221)
      (11893.0992 3919.0229) (11896.9771 3921.6031) (11899.5573 3925.4656) (11900.458 3930.0305) (11899.5573 3934.5802)
      (11896.9771 3938.4427) (11893.0992 3941.0229) (11888.5496 3941.9389) (11884.0 3941.0229) (11880.1221 3938.4427)
      (11877.542 3934.5802)
    ))
    ; P2941 -- see feature_dimensions_mm.csv
    ("06_ORNAMENT" 1 (
      (11916.7939 5331.5573) (11918.4885 5328.4122) (11923.1145 5325.8626) (11929.4198 5324.1985) (11935.7405 5323.3282)
      (11940.4733 5322.7481) (11942.5802 5321.6794) (11941.8473 5319.4351) (11938.916 5315.6794) (11935.0534 5310.6107)
      (11931.771 5304.9771) (11930.3053 5299.8931) (11931.3282 5296.4733) (11934.7481 5295.4504) (11939.8321 5296.916)
      (11945.4656 5300.1985) (11950.5344 5304.0458) (11954.2901 5306.9771) (11956.5344 5307.7099) (11957.6031 5305.6183)
      (11958.1985 5300.8855) (11959.0534 5294.5649) (11960.7176 5288.2595) (11963.2672 5283.6336) (11966.4122 5281.9389)
      (11969.5573 5283.6336) (11972.1069 5288.2595) (11973.771 5294.5649) (11974.626 5300.8855) (11975.2214 5305.6183)
      (11976.2901 5307.7099) (11978.5344 5306.9771) (11982.2901 5304.0458) (11987.3588 5300.1985) (11992.9924 5296.916)
      (11998.0763 5295.4504) (12001.4962 5296.4733) (12002.5191 5299.8931) (12001.0534 5304.9771) (11997.771 5310.6107)
      (11993.9084 5315.6794) (11990.9771 5319.4351) (11990.2443 5321.6794) (11992.3511 5322.7481) (11997.084 5323.3282)
      (12003.4046 5324.1985) (12009.7099 5325.8626) (12014.3359 5328.4122) (12015.2672 5330.1374) (12015.2672 5332.9618)
      (12014.3359 5334.7023) (12009.7099 5337.2519) (12003.4046 5338.916) (11997.084 5339.771) (11992.3511 5340.3664)
      (11990.2443 5341.4351) (11990.9771 5343.6794) (11993.9084 5347.4351) (11997.771 5352.5038) (12001.0534 5358.1374)
      (12002.5191 5363.2214) (12001.4962 5366.6412) (11998.0763 5367.6641) (11992.9924 5366.1985) (11987.3588 5362.916)
      (11982.2901 5359.0534) (11978.5344 5356.1221) (11976.2901 5355.3893) (11975.2214 5357.4962) (11974.626 5362.229)
      (11973.771 5368.5344) (11972.1069 5374.8397) (11969.5573 5379.4809) (11966.4122 5381.1756) (11963.2672 5379.4809)
      (11960.7176 5374.8397) (11959.0534 5368.5344) (11958.1985 5362.229) (11957.6031 5357.4962) (11956.5344 5355.3893)
      (11954.2901 5356.1221) (11950.5344 5359.0534) (11945.4656 5362.916) (11939.8321 5366.1985) (11934.7481 5367.6641)
      (11931.3282 5366.6412) (11930.3053 5363.2214) (11931.771 5358.1374) (11935.0534 5352.5038) (11938.916 5347.4351)
      (11941.8473 5343.6794) (11942.5802 5341.4351) (11940.4733 5340.3664) (11935.7405 5339.771) (11929.4198 5338.916)
      (11923.1145 5337.2519) (11918.4885 5334.7023)
    ))
    ; P2942 -- see feature_dimensions_mm.csv
    ("06_ORNAMENT" 1 (
      (11916.7939 5020.1069) (11918.4885 5016.9618) (11923.1145 5014.4122) (11929.4198 5012.7481) (11935.7405 5011.8779)
      (11940.4733 5011.2977) (11942.5802 5010.229) (11941.8473 5007.9847) (11938.916 5004.229) (11935.0534 4999.1603)
      (11931.771 4993.5267) (11930.3053 4988.4427) (11931.3282 4985.0229) (11934.7481 4984.0) (11939.8321 4985.4656)
      (11945.4656 4988.7481) (11950.5344 4992.5954) (11954.2901 4995.5267) (11956.5344 4996.2595) (11957.6031 4994.1679)
      (11958.1985 4989.4351) (11959.0534 4983.1145) (11960.7176 4976.8092) (11963.2672 4972.1832) (11966.4122 4970.4885)
      (11969.5573 4972.1832) (11972.1069 4976.8092) (11973.771 4983.1145) (11974.626 4989.4351) (11975.2214 4994.1679)
      (11976.2901 4996.2595) (11978.5344 4995.5267) (11982.2901 4992.5954) (11987.3588 4988.7481) (11992.9924 4985.4656)
      (11998.0763 4984.0) (12001.4962 4985.0229) (12002.5191 4988.4427) (12001.0534 4993.5267) (11997.771 4999.1603)
      (11993.9084 5004.229) (11990.9771 5007.9847) (11990.2443 5010.229) (11992.3511 5011.2977) (11997.084 5011.8779)
      (12003.4046 5012.7481) (12009.7099 5014.4122) (12014.3359 5016.9618) (12015.2672 5018.687) (12015.2672 5021.5115)
      (12014.3359 5023.2519) (12009.7099 5025.8015) (12003.4046 5027.4656) (11997.084 5028.3206) (11992.3511 5028.916)
      (11990.2443 5029.9847) (11990.9771 5032.229) (11993.9084 5035.9847) (11997.771 5041.0534) (12001.0534 5046.687)
      (12002.5191 5051.771) (12001.4962 5055.1908) (11998.0763 5056.2137) (11992.9924 5054.7481) (11987.3588 5051.4656)
      (11982.2901 5047.6031) (11978.5344 5044.6718) (11976.2901 5043.9389) (11975.2214 5046.0458) (11974.626 5050.7786)
      (11973.771 5057.084) (11972.1069 5063.3893) (11969.5573 5068.0305) (11966.4122 5069.7252) (11963.2672 5068.0305)
      (11960.7176 5063.3893) (11959.0534 5057.084) (11958.1985 5050.7786) (11957.6031 5046.0458) (11956.5344 5043.9389)
      (11954.2901 5044.6718) (11950.5344 5047.6031) (11945.4656 5051.4656) (11939.8321 5054.7481) (11934.7481 5056.2137)
      (11931.3282 5055.1908) (11930.3053 5051.771) (11931.771 5046.687) (11935.0534 5041.0534) (11938.916 5035.9847)
      (11941.8473 5032.229) (11942.5802 5029.9847) (11940.4733 5028.916) (11935.7405 5028.3206) (11929.4198 5027.4656)
      (11923.1145 5025.8015) (11918.4885 5023.2519)
    ))
    ; P2943 -- see feature_dimensions_mm.csv
    ("06_ORNAMENT" 1 (
      (11916.7939 4708.6565) (11918.4885 4705.5115) (11923.1145 4702.9618) (11929.4198 4701.2977) (11935.7405 4700.4275)
      (11940.4733 4699.8473) (11942.5802 4698.7786) (11941.8473 4696.5344) (11938.916 4692.7786) (11935.0534 4687.7099)
      (11931.771 4682.0763) (11930.3053 4676.9924) (11931.3282 4673.5725) (11934.7481 4672.5496) (11939.8321 4674.0153)
      (11945.4656 4677.2977) (11950.5344 4681.145) (11954.2901 4684.0763) (11956.5344 4684.8092) (11957.6031 4682.7176)
      (11958.1985 4677.9847) (11959.0534 4671.6641) (11960.7176 4665.3588) (11963.2672 4660.7328) (11966.4122 4659.0382)
      (11969.5573 4660.7328) (11972.1069 4665.3588) (11973.771 4671.6641) (11974.626 4677.9847) (11975.2214 4682.7176)
      (11976.2901 4684.8092) (11978.5344 4684.0763) (11982.2901 4681.145) (11987.3588 4677.2977) (11992.9924 4674.0153)
      (11998.0763 4672.5496) (12001.4962 4673.5725) (12002.5191 4676.9924) (12001.0534 4682.0763) (11997.771 4687.7099)
      (11993.9084 4692.7786) (11990.9771 4696.5344) (11990.2443 4698.7786) (11992.3511 4699.8473) (11997.084 4700.4275)
      (12003.4046 4701.2977) (12009.7099 4702.9618) (12014.3359 4705.5115) (12015.2672 4707.2366) (12015.2672 4710.0611)
      (12014.3359 4711.8015) (12009.7099 4714.3511) (12003.4046 4716.0153) (11997.084 4716.8702) (11992.3511 4717.4656)
      (11990.2443 4718.5344) (11990.9771 4720.7786) (11993.9084 4724.5344) (11997.771 4729.6031) (12001.0534 4735.2366)
      (12002.5191 4740.3206) (12001.4962 4743.7405) (11998.0763 4744.7634) (11992.9924 4743.2977) (11987.3588 4740.0153)
      (11982.2901 4736.1527) (11978.5344 4733.2214) (11976.2901 4732.4885) (11975.2214 4734.5954) (11974.626 4739.3282)
      (11973.771 4745.6336) (11972.1069 4751.9389) (11969.5573 4756.5802) (11966.4122 4758.2748) (11963.2672 4756.5802)
      (11960.7176 4751.9389) (11959.0534 4745.6336) (11958.1985 4739.3282) (11957.6031 4734.5954) (11956.5344 4732.4885)
      (11954.2901 4733.2214) (11950.5344 4736.1527) (11945.4656 4740.0153) (11939.8321 4743.2977) (11934.7481 4744.7634)
      (11931.3282 4743.7405) (11930.3053 4740.3206) (11931.771 4735.2366) (11935.0534 4729.6031) (11938.916 4724.5344)
      (11941.8473 4720.7786) (11942.5802 4718.5344) (11940.4733 4717.4656) (11935.7405 4716.8702) (11929.4198 4716.0153)
      (11923.1145 4714.3511) (11918.4885 4711.8015)
    ))
    ; P2944 -- see feature_dimensions_mm.csv
    ("06_ORNAMENT" 1 (
      (11916.7939 4085.7557) (11918.4885 4082.6107) (11923.1145 4080.0611) (11929.4198 4078.3969) (11935.7405 4077.5267)
      (11940.4733 4076.9466) (11942.5802 4075.8779) (11941.8473 4073.6336) (11938.916 4069.8779) (11935.0534 4064.8092)
      (11931.771 4059.1756) (11930.3053 4054.0916) (11931.3282 4050.6718) (11934.7481 4049.6489) (11939.8321 4051.1145)
      (11945.4656 4054.3969) (11950.5344 4058.2595) (11954.2901 4061.1756) (11956.5344 4061.9084) (11957.6031 4059.8168)
      (11958.1985 4055.084) (11959.0534 4048.7634) (11960.7176 4042.458) (11963.2672 4037.8321) (11966.4122 4036.1374)
      (11969.5573 4037.8321) (11972.1069 4042.458) (11973.771 4048.7634) (11974.626 4055.084) (11975.2214 4059.8168)
      (11976.2901 4061.9084) (11978.5344 4061.1756) (11982.2901 4058.2595) (11987.3588 4054.3969) (11992.9924 4051.1145)
      (11998.0763 4049.6489) (12001.4962 4050.6718) (12002.5191 4054.0916) (12001.0534 4059.1756) (11997.771 4064.8092)
      (11993.9084 4069.8779) (11990.9771 4073.6336) (11990.2443 4075.8779) (11992.3511 4076.9466) (11997.084 4077.5267)
      (12003.4046 4078.3969) (12009.7099 4080.0611) (12014.3359 4082.6107) (12015.2672 4084.3359) (12015.2672 4087.1603)
      (12014.3359 4088.9008) (12009.7099 4091.4504) (12003.4046 4093.1145) (11997.084 4093.9695) (11992.3511 4094.5649)
      (11990.2443 4095.6336) (11990.9771 4097.8779) (11993.9084 4101.6336) (11997.771 4106.7023) (12001.0534 4112.3359)
      (12002.5191 4117.4198) (12001.4962 4120.8397) (11998.0763 4121.8626) (11992.9924 4120.3969) (11987.3588 4117.1145)
      (11982.2901 4113.2519) (11978.5344 4110.3206) (11976.2901 4109.5878) (11975.2214 4111.6947) (11974.626 4116.4275)
      (11973.771 4122.7328) (11972.1069 4129.0382) (11969.5573 4133.6794) (11966.4122 4135.374) (11963.2672 4133.6794)
      (11960.7176 4129.0382) (11959.0534 4122.7328) (11958.1985 4116.4275) (11957.6031 4111.6947) (11956.5344 4109.5878)
      (11954.2901 4110.3206) (11950.5344 4113.2519) (11945.4656 4117.1145) (11939.8321 4120.3969) (11934.7481 4121.8626)
      (11931.3282 4120.8397) (11930.3053 4117.4198) (11931.771 4112.3359) (11935.0534 4106.7023) (11938.916 4101.6336)
      (11941.8473 4097.8779) (11942.5802 4095.6336) (11940.4733 4094.5649) (11935.7405 4093.9695) (11929.4198 4093.1145)
      (11923.1145 4091.4504) (11918.4885 4088.9008)
    ))
    ; P2945 -- see feature_dimensions_mm.csv
    ("06_ORNAMENT" 1 (
      (11948.0916 5409.4198) (11966.4122 5388.8092) (11984.7328 5409.4198) (11966.4122 5430.0305)
    ))
    ; P2946 -- see feature_dimensions_mm.csv
    ("06_ORNAMENT" 1 (
      (11948.0916 5097.9695) (11966.4122 5077.3588) (11984.7328 5097.9695) (11966.4122 5118.5802)
    ))
    ; P2947 -- see feature_dimensions_mm.csv
    ("06_ORNAMENT" 1 (
      (11948.0916 4786.5191) (11966.4122 4765.9084) (11984.7328 4786.5191) (11966.4122 4807.1298)
    ))
    ; P2948 -- see feature_dimensions_mm.csv
    ("06_ORNAMENT" 1 (
      (11948.0916 4163.6183) (11966.4122 4143.0076) (11984.7328 4163.6183) (11966.4122 4184.229)
    ))
    ; P2949 -- see feature_dimensions_mm.csv
    ("06_ORNAMENT" 1 (
      (11954.5038 5331.5573) (11955.4046 5326.9924) (11957.9847 5323.1298) (11961.8626 5320.5496) (11966.4122 5319.6489)
      (11970.9618 5320.5496) (11974.8397 5323.1298) (11977.4198 5326.9924) (11978.3206 5331.5573) (11977.4198 5336.1069)
      (11974.8397 5339.9695) (11970.9618 5342.5496) (11966.4122 5343.4656) (11961.8626 5342.5496) (11957.9847 5339.9695)
      (11955.4046 5336.1069)
    ))
    ; P2950 -- see feature_dimensions_mm.csv
    ("06_ORNAMENT" 1 (
      (11954.5038 5020.1069) (11955.4046 5015.542) (11957.9847 5011.6794) (11961.8626 5009.0992) (11966.4122 5008.1985)
      (11970.9618 5009.0992) (11974.8397 5011.6794) (11977.4198 5015.542) (11978.3206 5020.1069) (11977.4198 5024.6565)
      (11974.8397 5028.5191) (11970.9618 5031.0992) (11966.4122 5032.0153) (11961.8626 5031.0992) (11957.9847 5028.5191)
      (11955.4046 5024.6565)
    ))
    ; P2951 -- see feature_dimensions_mm.csv
    ("06_ORNAMENT" 1 (
      (11954.5038 4708.6565) (11955.4046 4704.0916) (11957.9847 4700.229) (11961.8626 4697.6489) (11966.4122 4696.7481)
      (11970.9618 4697.6489) (11974.8397 4700.229) (11977.4198 4704.0916) (11978.3206 4708.6565) (11977.4198 4713.2061)
      (11974.8397 4717.0687) (11970.9618 4719.6489) (11966.4122 4720.5649) (11961.8626 4719.6489) (11957.9847 4717.0687)
      (11955.4046 4713.2061)
    ))
    ; P2952 -- see feature_dimensions_mm.csv
    ("06_ORNAMENT" 1 (
      (11954.5038 4397.2061) (11955.4046 4392.6412) (11957.9847 4388.7786) (11961.8626 4386.1985) (11966.4122 4385.2977)
      (11970.9618 4386.1985) (11974.8397 4388.7786) (11977.4198 4392.6412) (11978.3206 4397.2061) (11977.4198 4401.7557)
      (11974.8397 4405.6183) (11970.9618 4408.1985) (11966.4122 4409.1145) (11961.8626 4408.1985) (11957.9847 4405.6183)
      (11955.4046 4401.7557)
    ))
    ; P2953 -- see feature_dimensions_mm.csv
    ("06_ORNAMENT" 1 (
      (11954.5038 4085.7557) (11955.4046 4081.1908) (11957.9847 4077.3282) (11961.8626 4074.7481) (11966.4122 4073.8473)
      (11970.9618 4074.7481) (11974.8397 4077.3282) (11977.4198 4081.1908) (11978.3206 4085.7557) (11977.4198 4090.3053)
      (11974.8397 4094.1679) (11970.9618 4096.7481) (11966.4122 4097.6641) (11961.8626 4096.7481) (11957.9847 4094.1679)
      (11955.4046 4090.3053)
    ))
    ; P2954 -- see feature_dimensions_mm.csv
    ("06_ORNAMENT" 1 (
      (11994.6565 5487.2824) (11996.3511 5484.1374) (12000.9771 5481.5878) (12007.2824 5479.9237) (12013.6031 5479.0534)
      (12015.2672 5478.855) (12015.2672 5495.7099) (12013.6031 5495.4962) (12007.2824 5494.6412) (12000.9771 5492.9771)
      (11996.3511 5490.4275)
    ))
    ; P2955 -- see feature_dimensions_mm.csv
    ("06_ORNAMENT" 1 (
      (11994.6565 5175.8321) (11996.3511 5172.687) (12000.9771 5170.1374) (12007.2824 5168.4733) (12013.6031 5167.6031)
      (12015.2672 5167.4046) (12015.2672 5184.2595) (12013.6031 5184.0458) (12007.2824 5183.1908) (12000.9771 5181.5267)
      (11996.3511 5178.9771)
    ))
    ; P2956 -- see feature_dimensions_mm.csv
    ("06_ORNAMENT" 1 (
      (11994.6565 4864.3817) (11996.3511 4861.2366) (12000.9771 4858.687) (12007.2824 4857.0229) (12013.6031 4856.1527)
      (12015.2672 4855.9542) (12015.2672 4872.8092) (12013.6031 4872.5954) (12007.2824 4871.7405) (12000.9771 4870.0763)
      (11996.3511 4867.5267)
    ))
    ; P2957 -- see feature_dimensions_mm.csv
    ("06_ORNAMENT" 1 (
      (11994.6565 4552.9313) (11996.3511 4549.7863) (12000.9771 4547.2366) (12007.2824 4545.5725) (12013.6031 4544.7023)
      (12015.2672 4544.5038) (12015.2672 4561.3588) (12013.6031 4561.145) (12007.2824 4560.2901) (12000.9771 4558.626)
      (11996.3511 4556.0763)
    ))
    ; P2958 -- see feature_dimensions_mm.csv
    ("06_ORNAMENT" 1 (
      (11994.6565 4241.4809) (11996.3511 4238.3359) (12000.9771 4235.7863) (12007.2824 4234.1221) (12013.6031 4233.2519)
      (12015.2672 4233.0534) (12015.2672 4249.9084) (12013.6031 4249.6947) (12007.2824 4248.8397) (12000.9771 4247.1756)
      (11996.3511 4244.626)
    ))
    ; P2959 -- see feature_dimensions_mm.csv
    ("06_ORNAMENT" 1 (
      (11994.6565 3930.0305) (11996.3511 3926.8855) (12000.9771 3924.3359) (12007.2824 3922.6718) (12013.6031 3921.8015)
      (12015.2672 3921.6031) (12015.2672 3938.458) (12013.6031 3938.2443) (12007.2824 3937.3893) (12000.9771 3935.7252)
      (11996.3511 3933.1756)
    ))
    ; P2960 -- see feature_dimensions_mm.csv
    ("06_ORNAMENT" 1 (
      (12008.1679 5518.9466) (12009.6336 5513.8626) (12012.916 5508.229) (12015.2672 5505.145) (12015.2672 5522.626)
      (12012.6107 5523.3893) (12009.1908 5522.3664)
    ))
    ; P2961 -- see feature_dimensions_mm.csv
    ("06_ORNAMENT" 1 (
      (12008.1679 5455.6183) (12009.1908 5452.1985) (12012.6107 5451.1756) (12015.2672 5451.9389) (12015.2672 5469.4198)
      (12012.916 5466.3359) (12009.6336 5460.7023)
    ))
    ; P2962 -- see feature_dimensions_mm.csv
    ("06_ORNAMENT" 1 (
      (12008.1679 5207.4962) (12009.6336 5202.4122) (12012.916 5196.7786) (12015.2672 5193.6947) (12015.2672 5211.1756)
      (12012.6107 5211.9389) (12009.1908 5210.916)
    ))
    ; P2963 -- see feature_dimensions_mm.csv
    ("06_ORNAMENT" 1 (
      (12008.1679 5144.1679) (12009.1908 5140.7481) (12012.6107 5139.7252) (12015.2672 5140.4885) (12015.2672 5157.9695)
      (12012.916 5154.8855) (12009.6336 5149.2519)
    ))
    ; P2964 -- see feature_dimensions_mm.csv
    ("06_ORNAMENT" 1 (
      (12008.1679 4896.0458) (12009.6336 4890.9618) (12012.916 4885.3282) (12015.2672 4882.2443) (12015.2672 4899.7252)
      (12012.6107 4900.4885) (12009.1908 4899.4656)
    ))
    ; P2965 -- see feature_dimensions_mm.csv
    ("06_ORNAMENT" 1 (
      (12008.1679 4832.7176) (12009.1908 4829.2977) (12012.6107 4828.2748) (12015.2672 4829.0382) (12015.2672 4846.5191)
      (12012.916 4843.4351) (12009.6336 4837.8015)
    ))
    ; P2966 -- see feature_dimensions_mm.csv
    ("06_ORNAMENT" 1 (
      (12008.1679 4584.5954) (12009.6336 4579.5115) (12012.916 4573.8779) (12015.2672 4570.7939) (12015.2672 4588.2748)
      (12012.6107 4589.0382) (12009.1908 4588.0153)
    ))
    ; P2967 -- see feature_dimensions_mm.csv
    ("06_ORNAMENT" 1 (
      (12008.1679 4521.2672) (12009.1908 4517.8473) (12012.6107 4516.8244) (12015.2672 4517.5878) (12015.2672 4535.0687)
      (12012.916 4531.9847) (12009.6336 4526.3511)
    ))
    ; P2968 -- see feature_dimensions_mm.csv
    ("06_ORNAMENT" 1 (
      (12008.1679 4273.145) (12009.6336 4268.0611) (12012.916 4262.4275) (12015.2672 4259.3435) (12015.2672 4276.8244)
      (12012.6107 4277.5878) (12009.1908 4276.5649)
    ))
    ; P2969 -- see feature_dimensions_mm.csv
    ("06_ORNAMENT" 1 (
      (12008.1679 4209.8168) (12009.1908 4206.3969) (12012.6107 4205.374) (12015.2672 4206.1374) (12015.2672 4223.6183)
      (12012.916 4220.5344) (12009.6336 4214.9008)
    ))
    ; P2970 -- see feature_dimensions_mm.csv
    ("06_ORNAMENT" 1 (
      (12008.1679 3961.6947) (12009.6336 3956.6107) (12012.916 3950.9771) (12015.2672 3947.8931) (12015.2672 3965.374)
      (12012.6107 3966.1374) (12009.1908 3965.1145)
    ))
    ; P2971 -- see feature_dimensions_mm.csv
    ("06_ORNAMENT" 1 (
      (12008.1679 3898.3664) (12009.1908 3894.9466) (12012.6107 3893.9237) (12015.2672 3894.687) (12015.2672 3912.1679)
      (12012.916 3909.084) (12009.6336 3903.4504)
    ))
    ; P2972 -- see feature_dimensions_mm.csv
    ("06_ORNAMENT" 1 (
      (12015.2672 7374.0458) (12076.3359 7343.5115) (12137.4046 7374.0458) (12076.3359 7404.5802)
    ))
    ; P2973 -- see feature_dimensions_mm.csv
    ("06_ORNAMENT" 1 (
      (12015.2672 7282.4427) (12076.3359 7251.9084) (12137.4046 7282.4427) (12076.3359 7312.9771)
    ))
    ; P2974 -- see feature_dimensions_mm.csv
    ("06_ORNAMENT" 1 (
      (12015.2672 7190.8397) (12076.3359 7160.3053) (12137.4046 7190.8397) (12076.3359 7221.374)
    ))
    ; P2975 -- see feature_dimensions_mm.csv
    ("06_ORNAMENT" 1 (
      (12015.2672 6061.0687) (12017.5115 6046.916) (12024.0153 6034.1527) (12034.1527 6024.0153) (12046.916 6017.5115)
      (12061.0687 6015.2672) (12075.2214 6017.5115) (12087.9847 6024.0153) (12098.1221 6034.1527) (12104.626 6046.916)
      (12106.8702 6061.0687) (12104.626 6075.2214) (12098.1221 6087.9847) (12087.9847 6098.1221) (12075.2214 6104.626)
      (12061.0687 6106.8702) (12046.916 6104.626) (12034.1527 6098.1221) (12024.0153 6087.9847) (12017.5115 6075.2214)
    ))
    ; P2976 -- see feature_dimensions_mm.csv
    ("06_ORNAMENT" 1 (
      (12106.8702 5412.855) (12106.8702 5405.9847) (12122.1374 5388.8092) (12140.458 5409.4198) (12122.1374 5430.0305)
    ))
    ; P2977 -- see feature_dimensions_mm.csv
    ("06_ORNAMENT" 1 (
      (12106.8702 5358.5802) (12106.8702 5304.5344) (12110.0153 5306.9771) (12112.2595 5307.7099) (12113.3282 5305.6183)
      (12113.9237 5300.8855) (12114.7786 5294.5649) (12116.4427 5288.2595) (12118.9924 5283.6336) (12122.1374 5281.9389)
      (12125.2824 5283.6336) (12127.8321 5288.2595) (12129.4962 5294.5649) (12130.3511 5300.8855) (12130.9466 5305.6183)
      (12132.0153 5307.7099) (12134.2595 5306.9771) (12138.0153 5304.0458) (12143.084 5300.1985) (12148.7176 5296.916)
      (12153.8015 5295.4504) (12157.2214 5296.4733) (12158.2443 5299.8931) (12156.7786 5304.9771) (12153.4962 5310.6107)
      (12149.6336 5315.6794) (12146.7023 5319.4351) (12145.9695 5321.6794) (12148.0763 5322.7481) (12152.8092 5323.3282)
      (12159.1298 5324.1985) (12165.4351 5325.8626) (12170.0611 5328.4122) (12171.7557 5331.5573) (12170.0611 5334.7023)
      (12165.4351 5337.2519) (12159.1298 5338.916) (12152.8092 5339.771) (12148.0763 5340.3664) (12145.9695 5341.4351)
      (12146.7023 5343.6794) (12149.6336 5347.4351) (12153.4962 5352.5038) (12156.7786 5358.1374) (12158.2443 5363.2214)
      (12157.2214 5366.6412) (12153.8015 5367.6641) (12148.7176 5366.1985) (12143.084 5362.916) (12138.0153 5359.0534)
      (12134.2595 5356.1221) (12132.0153 5355.3893) (12130.9466 5357.4962) (12130.3511 5362.229) (12129.4962 5368.5344)
      (12127.8321 5374.8397) (12125.2824 5379.4809) (12122.1374 5381.1756) (12118.9924 5379.4809) (12116.4427 5374.8397)
      (12114.7786 5368.5344) (12113.9237 5362.229) (12113.3282 5357.4962) (12112.2595 5355.3893) (12110.0153 5356.1221)
    ))
    ; P2978 -- see feature_dimensions_mm.csv
    ("06_ORNAMENT" 1 (
      (12106.8702 5101.4046) (12106.8702 5094.5344) (12122.1374 5077.3588) (12140.458 5097.9695) (12122.1374 5118.5802)
    ))
    ; P2979 -- see feature_dimensions_mm.csv
    ("06_ORNAMENT" 1 (
      (12106.8702 5047.1298) (12106.8702 4993.084) (12110.0153 4995.5267) (12112.2595 4996.2595) (12113.3282 4994.1679)
      (12113.9237 4989.4351) (12114.7786 4983.1145) (12116.4427 4976.8092) (12118.9924 4972.1832) (12122.1374 4970.4885)
      (12125.2824 4972.1832) (12127.8321 4976.8092) (12129.4962 4983.1145) (12130.3511 4989.4351) (12130.9466 4994.1679)
      (12132.0153 4996.2595) (12134.2595 4995.5267) (12138.0153 4992.5954) (12143.084 4988.7481) (12148.7176 4985.4656)
      (12153.8015 4984.0) (12157.2214 4985.0229) (12158.2443 4988.4427) (12156.7786 4993.5267) (12153.4962 4999.1603)
      (12149.6336 5004.229) (12146.7023 5007.9847) (12145.9695 5010.229) (12148.0763 5011.2977) (12152.8092 5011.8779)
      (12159.1298 5012.7481) (12165.4351 5014.4122) (12170.0611 5016.9618) (12171.7557 5020.1069) (12170.0611 5023.2519)
      (12165.4351 5025.8015) (12159.1298 5027.4656) (12152.8092 5028.3206) (12148.0763 5028.916) (12145.9695 5029.9847)
      (12146.7023 5032.229) (12149.6336 5035.9847) (12153.4962 5041.0534) (12156.7786 5046.687) (12158.2443 5051.771)
      (12157.2214 5055.1908) (12153.8015 5056.2137) (12148.7176 5054.7481) (12143.084 5051.4656) (12138.0153 5047.6031)
      (12134.2595 5044.6718) (12132.0153 5043.9389) (12130.9466 5046.0458) (12130.3511 5050.7786) (12129.4962 5057.084)
      (12127.8321 5063.3893) (12125.2824 5068.0305) (12122.1374 5069.7252) (12118.9924 5068.0305) (12116.4427 5063.3893)
      (12114.7786 5057.084) (12113.9237 5050.7786) (12113.3282 5046.0458) (12112.2595 5043.9389) (12110.0153 5044.6718)
    ))
    ; P2980 -- see feature_dimensions_mm.csv
    ("06_ORNAMENT" 1 (
      (12106.8702 4789.9542) (12106.8702 4783.084) (12122.1374 4765.9084) (12140.458 4786.5191) (12122.1374 4807.1298)
    ))
    ; P2981 -- see feature_dimensions_mm.csv
    ("06_ORNAMENT" 1 (
      (12106.8702 4735.6794) (12106.8702 4681.6336) (12110.0153 4684.0763) (12112.2595 4684.8092) (12113.3282 4682.7176)
      (12113.9237 4677.9847) (12114.7786 4671.6641) (12116.4427 4665.3588) (12118.9924 4660.7328) (12122.1374 4659.0382)
      (12125.2824 4660.7328) (12127.8321 4665.3588) (12129.4962 4671.6641) (12130.3511 4677.9847) (12130.9466 4682.7176)
      (12132.0153 4684.8092) (12134.2595 4684.0763) (12138.0153 4681.145) (12143.084 4677.2977) (12148.7176 4674.0153)
      (12153.8015 4672.5496) (12157.2214 4673.5725) (12158.2443 4676.9924) (12156.7786 4682.0763) (12153.4962 4687.7099)
      (12149.6336 4692.7786) (12146.7023 4696.5344) (12145.9695 4698.7786) (12148.0763 4699.8473) (12152.8092 4700.4275)
      (12159.1298 4701.2977) (12165.4351 4702.9618) (12170.0611 4705.5115) (12171.7557 4708.6565) (12170.0611 4711.8015)
      (12165.4351 4714.3511) (12159.1298 4716.0153) (12152.8092 4716.8702) (12148.0763 4717.4656) (12145.9695 4718.5344)
      (12146.7023 4720.7786) (12149.6336 4724.5344) (12153.4962 4729.6031) (12156.7786 4735.2366) (12158.2443 4740.3206)
      (12157.2214 4743.7405) (12153.8015 4744.7634) (12148.7176 4743.2977) (12143.084 4740.0153) (12138.0153 4736.1527)
      (12134.2595 4733.2214) (12132.0153 4732.4885) (12130.9466 4734.5954) (12130.3511 4739.3282) (12129.4962 4745.6336)
      (12127.8321 4751.9389) (12125.2824 4756.5802) (12122.1374 4758.2748) (12118.9924 4756.5802) (12116.4427 4751.9389)
      (12114.7786 4745.6336) (12113.9237 4739.3282) (12113.3282 4734.5954) (12112.2595 4732.4885) (12110.0153 4733.2214)
    ))
    ; P2982 -- see feature_dimensions_mm.csv
    ("06_ORNAMENT" 1 (
      (12106.8702 4167.0534) (12106.8702 4160.1832) (12122.1374 4143.0076) (12140.458 4163.6183) (12122.1374 4184.229)
    ))
    ; P2983 -- see feature_dimensions_mm.csv
    ("06_ORNAMENT" 1 (
      (12106.8702 4112.7786) (12106.8702 4058.7328) (12110.0153 4061.1756) (12112.2595 4061.9084) (12113.3282 4059.8168)
      (12113.9237 4055.084) (12114.7786 4048.7634) (12116.4427 4042.458) (12118.9924 4037.8321) (12122.1374 4036.1374)
      (12125.2824 4037.8321) (12127.8321 4042.458) (12129.4962 4048.7634) (12130.3511 4055.084) (12130.9466 4059.8168)
      (12132.0153 4061.9084) (12134.2595 4061.1756) (12138.0153 4058.2595) (12143.084 4054.3969) (12148.7176 4051.1145)
      (12153.8015 4049.6489) (12157.2214 4050.6718) (12158.2443 4054.0916) (12156.7786 4059.1756) (12153.4962 4064.8092)
      (12149.6336 4069.8779) (12146.7023 4073.6336) (12145.9695 4075.8779) (12148.0763 4076.9466) (12152.8092 4077.5267)
      (12159.1298 4078.3969) (12165.4351 4080.0611) (12170.0611 4082.6107) (12171.7557 4085.7557) (12170.0611 4088.9008)
      (12165.4351 4091.4504) (12159.1298 4093.1145) (12152.8092 4093.9695) (12148.0763 4094.5649) (12145.9695 4095.6336)
      (12146.7023 4097.8779) (12149.6336 4101.6336) (12153.4962 4106.7023) (12156.7786 4112.3359) (12158.2443 4117.4198)
      (12157.2214 4120.8397) (12153.8015 4121.8626) (12148.7176 4120.3969) (12143.084 4117.1145) (12138.0153 4113.2519)
      (12134.2595 4110.3206) (12132.0153 4109.5878) (12130.9466 4111.6947) (12130.3511 4116.4275) (12129.4962 4122.7328)
      (12127.8321 4129.0382) (12125.2824 4133.6794) (12122.1374 4135.374) (12118.9924 4133.6794) (12116.4427 4129.0382)
      (12114.7786 4122.7328) (12113.9237 4116.4275) (12113.3282 4111.6947) (12112.2595 4109.5878) (12110.0153 4110.3206)
    ))
    ; P2984 -- see feature_dimensions_mm.csv
    ("06_ORNAMENT" 1 (
      (12110.229 5331.5573) (12111.1298 5326.9924) (12113.7099 5323.1298) (12117.5878 5320.5496) (12122.1374 5319.6489)
      (12126.687 5320.5496) (12130.5649 5323.1298) (12133.145 5326.9924) (12134.0458 5331.5573) (12133.145 5336.1069)
      (12130.5649 5339.9695) (12126.687 5342.5496) (12122.1374 5343.4656) (12117.5878 5342.5496) (12113.7099 5339.9695)
      (12111.1298 5336.1069)
    ))
    ; P2985 -- see feature_dimensions_mm.csv
    ("06_ORNAMENT" 1 (
      (12110.229 5020.1069) (12111.1298 5015.542) (12113.7099 5011.6794) (12117.5878 5009.0992) (12122.1374 5008.1985)
      (12126.687 5009.0992) (12130.5649 5011.6794) (12133.145 5015.542) (12134.0458 5020.1069) (12133.145 5024.6565)
      (12130.5649 5028.5191) (12126.687 5031.0992) (12122.1374 5032.0153) (12117.5878 5031.0992) (12113.7099 5028.5191)
      (12111.1298 5024.6565)
    ))
    ; P2986 -- see feature_dimensions_mm.csv
    ("06_ORNAMENT" 1 (
      (12110.229 4708.6565) (12111.1298 4704.0916) (12113.7099 4700.229) (12117.5878 4697.6489) (12122.1374 4696.7481)
      (12126.687 4697.6489) (12130.5649 4700.229) (12133.145 4704.0916) (12134.0458 4708.6565) (12133.145 4713.2061)
      (12130.5649 4717.0687) (12126.687 4719.6489) (12122.1374 4720.5649) (12117.5878 4719.6489) (12113.7099 4717.0687)
      (12111.1298 4713.2061)
    ))
    ; P2987 -- see feature_dimensions_mm.csv
    ("06_ORNAMENT" 1 (
      (12110.229 4397.2061) (12111.1298 4392.6412) (12113.7099 4388.7786) (12117.5878 4386.1985) (12122.1374 4385.2977)
      (12126.687 4386.1985) (12130.5649 4388.7786) (12133.145 4392.6412) (12134.0458 4397.2061) (12133.145 4401.7557)
      (12130.5649 4405.6183) (12126.687 4408.1985) (12122.1374 4409.1145) (12117.5878 4408.1985) (12113.7099 4405.6183)
      (12111.1298 4401.7557)
    ))
    ; P2988 -- see feature_dimensions_mm.csv
    ("06_ORNAMENT" 1 (
      (12110.229 4085.7557) (12111.1298 4081.1908) (12113.7099 4077.3282) (12117.5878 4074.7481) (12122.1374 4073.8473)
      (12126.687 4074.7481) (12130.5649 4077.3282) (12133.145 4081.1908) (12134.0458 4085.7557) (12133.145 4090.3053)
      (12130.5649 4094.1679) (12126.687 4096.7481) (12122.1374 4097.6641) (12117.5878 4096.7481) (12113.7099 4094.1679)
      (12111.1298 4090.3053)
    ))
    ; P2989 -- see feature_dimensions_mm.csv
    ("06_ORNAMENT" 1 (
      (12150.3817 5487.2824) (12152.0763 5484.1374) (12156.7023 5481.5878) (12163.0076 5479.9237) (12169.3282 5479.0534)
      (12174.0611 5478.4733) (12176.1679 5477.4046) (12175.4351 5475.1603) (12172.5038 5471.4046) (12168.6412 5466.3359)
      (12165.3588 5460.7023) (12163.8931 5455.6183) (12164.916 5452.1985) (12168.3359 5451.1756) (12173.4198 5452.6412)
      (12179.0534 5455.9237) (12184.1221 5459.771) (12187.8779 5462.7023) (12190.1221 5463.4351) (12191.1908 5461.3435)
      (12191.7863 5456.6107) (12192.6412 5450.2901) (12194.3053 5443.9847) (12196.855 5439.3588) (12200.0 5437.6641)
      (12203.145 5439.3588) (12205.6947 5443.9847) (12207.3588 5450.2901) (12208.2137 5456.6107) (12208.8092 5461.3435)
      (12209.8779 5463.4351) (12212.1221 5462.7023) (12215.8779 5459.771) (12220.9466 5455.9237) (12226.5802 5452.6412)
      (12231.6641 5451.1756) (12235.084 5452.1985) (12236.1069 5455.6183) (12234.6412 5460.7023) (12231.3588 5466.3359)
      (12227.4962 5471.4046) (12224.5649 5475.1603) (12223.8321 5477.4046) (12225.9389 5478.4733) (12230.6718 5479.0534)
      (12236.9924 5479.9237) (12243.2977 5481.5878) (12247.9237 5484.1374) (12249.6183 5487.2824) (12247.9237 5490.4275)
      (12243.2977 5492.9771) (12236.9924 5494.6412) (12230.6718 5495.4962) (12225.9389 5496.0916) (12223.8321 5497.1603)
      (12224.5649 5499.4046) (12227.4962 5503.1603) (12231.3588 5508.229) (12234.6412 5513.8626) (12236.1069 5518.9466)
      (12235.084 5522.3664) (12231.6641 5523.3893) (12226.5802 5521.9237) (12220.9466 5518.6412) (12215.8779 5514.7786)
      (12212.1221 5511.8473) (12209.8779 5511.1145) (12208.8092 5513.2214) (12208.2137 5517.9542) (12207.3588 5524.2595)
      (12205.6947 5530.5649) (12203.145 5535.2061) (12200.0 5536.9008) (12196.855 5535.2061) (12194.3053 5530.5649)
      (12192.6412 5524.2595) (12191.7863 5517.9542) (12191.1908 5513.2214) (12190.1221 5511.1145) (12187.8779 5511.8473)
      (12184.1221 5514.7786) (12179.0534 5518.6412) (12173.4198 5521.9237) (12168.3359 5523.3893) (12164.916 5522.3664)
      (12163.8931 5518.9466) (12165.3588 5513.8626) (12168.6412 5508.229) (12172.5038 5503.1603) (12175.4351 5499.4046)
      (12176.1679 5497.1603) (12174.0611 5496.0916) (12169.3282 5495.4962) (12163.0076 5494.6412) (12156.7023 5492.9771)
      (12152.0763 5490.4275)
    ))
    ; P2990 -- see feature_dimensions_mm.csv
    ("06_ORNAMENT" 1 (
      (12150.3817 5175.8321) (12152.0763 5172.687) (12156.7023 5170.1374) (12163.0076 5168.4733) (12169.3282 5167.6031)
      (12174.0611 5167.0229) (12176.1679 5165.9542) (12175.4351 5163.7099) (12172.5038 5159.9542) (12168.6412 5154.8855)
      (12165.3588 5149.2519) (12163.8931 5144.1679) (12164.916 5140.7481) (12168.3359 5139.7252) (12173.4198 5141.1908)
      (12179.0534 5144.4733) (12184.1221 5148.3206) (12187.8779 5151.2519) (12190.1221 5151.9847) (12191.1908 5149.8931)
      (12191.7863 5145.1603) (12192.6412 5138.8397) (12194.3053 5132.5344) (12196.855 5127.9084) (12200.0 5126.2137)
      (12203.145 5127.9084) (12205.6947 5132.5344) (12207.3588 5138.8397) (12208.2137 5145.1603) (12208.8092 5149.8931)
      (12209.8779 5151.9847) (12212.1221 5151.2519) (12215.8779 5148.3206) (12220.9466 5144.4733) (12226.5802 5141.1908)
      (12231.6641 5139.7252) (12235.084 5140.7481) (12236.1069 5144.1679) (12234.6412 5149.2519) (12231.3588 5154.8855)
      (12227.4962 5159.9542) (12224.5649 5163.7099) (12223.8321 5165.9542) (12225.9389 5167.0229) (12230.6718 5167.6031)
      (12236.9924 5168.4733) (12243.2977 5170.1374) (12247.9237 5172.687) (12249.6183 5175.8321) (12247.9237 5178.9771)
      (12243.2977 5181.5267) (12236.9924 5183.1908) (12230.6718 5184.0458) (12225.9389 5184.6412) (12223.8321 5185.7099)
      (12224.5649 5187.9542) (12227.4962 5191.7099) (12231.3588 5196.7786) (12234.6412 5202.4122) (12236.1069 5207.4962)
      (12235.084 5210.916) (12231.6641 5211.9389) (12226.5802 5210.4733) (12220.9466 5207.1908) (12215.8779 5203.3282)
      (12212.1221 5200.3969) (12209.8779 5199.6641) (12208.8092 5201.771) (12208.2137 5206.5038) (12207.3588 5212.8092)
      (12205.6947 5219.1145) (12203.145 5223.7557) (12200.0 5225.4504) (12196.855 5223.7557) (12194.3053 5219.1145)
      (12192.6412 5212.8092) (12191.7863 5206.5038) (12191.1908 5201.771) (12190.1221 5199.6641) (12187.8779 5200.3969)
      (12184.1221 5203.3282) (12179.0534 5207.1908) (12173.4198 5210.4733) (12168.3359 5211.9389) (12164.916 5210.916)
      (12163.8931 5207.4962) (12165.3588 5202.4122) (12168.6412 5196.7786) (12172.5038 5191.7099) (12175.4351 5187.9542)
      (12176.1679 5185.7099) (12174.0611 5184.6412) (12169.3282 5184.0458) (12163.0076 5183.1908) (12156.7023 5181.5267)
      (12152.0763 5178.9771)
    ))
    ; P2991 -- see feature_dimensions_mm.csv
    ("06_ORNAMENT" 1 (
      (12150.3817 4864.3817) (12152.0763 4861.2366) (12156.7023 4858.687) (12163.0076 4857.0229) (12169.3282 4856.1527)
      (12174.0611 4855.5725) (12176.1679 4854.5038) (12175.4351 4852.2595) (12172.5038 4848.5038) (12168.6412 4843.4351)
      (12165.3588 4837.8015) (12163.8931 4832.7176) (12164.916 4829.2977) (12168.3359 4828.2748) (12173.4198 4829.7405)
      (12179.0534 4833.0229) (12184.1221 4836.8702) (12187.8779 4839.8015) (12190.1221 4840.5344) (12191.1908 4838.4427)
      (12191.7863 4833.7099) (12192.6412 4827.3893) (12194.3053 4821.084) (12196.855 4816.458) (12200.0 4814.7634)
      (12203.145 4816.458) (12205.6947 4821.084) (12207.3588 4827.3893) (12208.2137 4833.7099) (12208.8092 4838.4427)
      (12209.8779 4840.5344) (12212.1221 4839.8015) (12215.8779 4836.8702) (12220.9466 4833.0229) (12226.5802 4829.7405)
      (12231.6641 4828.2748) (12235.084 4829.2977) (12236.1069 4832.7176) (12234.6412 4837.8015) (12231.3588 4843.4351)
      (12227.4962 4848.5038) (12224.5649 4852.2595) (12223.8321 4854.5038) (12225.9389 4855.5725) (12230.6718 4856.1527)
      (12236.9924 4857.0229) (12243.2977 4858.687) (12247.9237 4861.2366) (12249.6183 4864.3817) (12247.9237 4867.5267)
      (12243.2977 4870.0763) (12236.9924 4871.7405) (12230.6718 4872.5954) (12225.9389 4873.1908) (12223.8321 4874.2595)
      (12224.5649 4876.5038) (12227.4962 4880.2595) (12231.3588 4885.3282) (12234.6412 4890.9618) (12236.1069 4896.0458)
      (12235.084 4899.4656) (12231.6641 4900.4885) (12226.5802 4899.0229) (12220.9466 4895.7405) (12215.8779 4891.8779)
      (12212.1221 4888.9466) (12209.8779 4888.2137) (12208.8092 4890.3206) (12208.2137 4895.0534) (12207.3588 4901.3588)
      (12205.6947 4907.6641) (12203.145 4912.3053) (12200.0 4914.0) (12196.855 4912.3053) (12194.3053 4907.6641)
      (12192.6412 4901.3588) (12191.7863 4895.0534) (12191.1908 4890.3206) (12190.1221 4888.2137) (12187.8779 4888.9466)
      (12184.1221 4891.8779) (12179.0534 4895.7405) (12173.4198 4899.0229) (12168.3359 4900.4885) (12164.916 4899.4656)
      (12163.8931 4896.0458) (12165.3588 4890.9618) (12168.6412 4885.3282) (12172.5038 4880.2595) (12175.4351 4876.5038)
      (12176.1679 4874.2595) (12174.0611 4873.1908) (12169.3282 4872.5954) (12163.0076 4871.7405) (12156.7023 4870.0763)
      (12152.0763 4867.5267)
    ))
    ; P2992 -- see feature_dimensions_mm.csv
    ("06_ORNAMENT" 1 (
      (12150.3817 4552.9313) (12152.0763 4549.7863) (12156.7023 4547.2366) (12163.0076 4545.5725) (12169.3282 4544.7023)
      (12174.0611 4544.1221) (12176.1679 4543.0534) (12175.4351 4540.8092) (12172.5038 4537.0534) (12168.6412 4531.9847)
      (12165.3588 4526.3511) (12163.8931 4521.2672) (12164.916 4517.8473) (12168.3359 4516.8244) (12173.4198 4518.2901)
      (12179.0534 4521.5725) (12184.1221 4525.4198) (12187.8779 4528.3511) (12190.1221 4529.084) (12191.1908 4526.9924)
      (12191.7863 4522.2595) (12192.6412 4515.9389) (12194.3053 4509.6336) (12196.855 4505.0076) (12200.0 4503.313)
      (12203.145 4505.0076) (12205.6947 4509.6336) (12207.3588 4515.9389) (12208.2137 4522.2595) (12208.8092 4526.9924)
      (12209.8779 4529.084) (12212.1221 4528.3511) (12215.8779 4525.4198) (12220.9466 4521.5725) (12226.5802 4518.2901)
      (12231.6641 4516.8244) (12235.084 4517.8473) (12236.1069 4521.2672) (12234.6412 4526.3511) (12231.3588 4531.9847)
      (12227.4962 4537.0534) (12224.5649 4540.8092) (12223.8321 4543.0534) (12225.9389 4544.1221) (12230.6718 4544.7023)
      (12236.9924 4545.5725) (12243.2977 4547.2366) (12247.9237 4549.7863) (12249.6183 4552.9313) (12247.9237 4556.0763)
      (12243.2977 4558.626) (12236.9924 4560.2901) (12230.6718 4561.145) (12225.9389 4561.7405) (12223.8321 4562.8092)
      (12224.5649 4565.0534) (12227.4962 4568.8092) (12231.3588 4573.8779) (12234.6412 4579.5115) (12236.1069 4584.5954)
      (12235.084 4588.0153) (12231.6641 4589.0382) (12226.5802 4587.5725) (12220.9466 4584.2901) (12215.8779 4580.4275)
      (12212.1221 4577.4962) (12209.8779 4576.7634) (12208.8092 4578.8702) (12208.2137 4583.6031) (12207.3588 4589.9084)
      (12205.6947 4596.2137) (12203.145 4600.855) (12200.0 4602.5496) (12196.855 4600.855) (12194.3053 4596.2137)
      (12192.6412 4589.9084) (12191.7863 4583.6031) (12191.1908 4578.8702) (12190.1221 4576.7634) (12187.8779 4577.4962)
      (12184.1221 4580.4275) (12179.0534 4584.2901) (12173.4198 4587.5725) (12168.3359 4589.0382) (12164.916 4588.0153)
      (12163.8931 4584.5954) (12165.3588 4579.5115) (12168.6412 4573.8779) (12172.5038 4568.8092) (12175.4351 4565.0534)
      (12176.1679 4562.8092) (12174.0611 4561.7405) (12169.3282 4561.145) (12163.0076 4560.2901) (12156.7023 4558.626)
      (12152.0763 4556.0763)
    ))
    ; P2993 -- see feature_dimensions_mm.csv
    ("06_ORNAMENT" 1 (
      (12150.3817 4241.4809) (12152.0763 4238.3359) (12156.7023 4235.7863) (12163.0076 4234.1221) (12169.3282 4233.2519)
      (12174.0611 4232.6718) (12176.1679 4231.6031) (12175.4351 4229.3588) (12172.5038 4225.6031) (12168.6412 4220.5344)
      (12165.3588 4214.9008) (12163.8931 4209.8168) (12164.916 4206.3969) (12168.3359 4205.374) (12173.4198 4206.8397)
      (12179.0534 4210.1221) (12184.1221 4213.9695) (12187.8779 4216.9008) (12190.1221 4217.6336) (12191.1908 4215.542)
      (12191.7863 4210.8092) (12192.6412 4204.4885) (12194.3053 4198.1832) (12196.855 4193.5573) (12200.0 4191.8626)
      (12203.145 4193.5573) (12205.6947 4198.1832) (12207.3588 4204.4885) (12208.2137 4210.8092) (12208.8092 4215.542)
      (12209.8779 4217.6336) (12212.1221 4216.9008) (12215.8779 4213.9695) (12220.9466 4210.1221) (12226.5802 4206.8397)
      (12231.6641 4205.374) (12235.084 4206.3969) (12236.1069 4209.8168) (12234.6412 4214.9008) (12231.3588 4220.5344)
      (12227.4962 4225.6031) (12224.5649 4229.3588) (12223.8321 4231.6031) (12225.9389 4232.6718) (12230.6718 4233.2519)
      (12236.9924 4234.1221) (12243.2977 4235.7863) (12247.9237 4238.3359) (12249.6183 4241.4809) (12247.9237 4244.626)
      (12243.2977 4247.1756) (12236.9924 4248.8397) (12230.6718 4249.6947) (12225.9389 4250.2901) (12223.8321 4251.3588)
      (12224.5649 4253.6031) (12227.4962 4257.3588) (12231.3588 4262.4275) (12234.6412 4268.0611) (12236.1069 4273.145)
      (12235.084 4276.5649) (12231.6641 4277.5878) (12226.5802 4276.1221) (12220.9466 4272.8397) (12215.8779 4268.9771)
      (12212.1221 4266.0458) (12209.8779 4265.313) (12208.8092 4267.4198) (12208.2137 4272.1527) (12207.3588 4278.458)
      (12205.6947 4284.7634) (12203.145 4289.4046) (12200.0 4291.0992) (12196.855 4289.4046) (12194.3053 4284.7634)
      (12192.6412 4278.458) (12191.7863 4272.1527) (12191.1908 4267.4198) (12190.1221 4265.313) (12187.8779 4266.0458)
      (12184.1221 4268.9771) (12179.0534 4272.8397) (12173.4198 4276.1221) (12168.3359 4277.5878) (12164.916 4276.5649)
      (12163.8931 4273.145) (12165.3588 4268.0611) (12168.6412 4262.4275) (12172.5038 4257.3588) (12175.4351 4253.6031)
      (12176.1679 4251.3588) (12174.0611 4250.2901) (12169.3282 4249.6947) (12163.0076 4248.8397) (12156.7023 4247.1756)
      (12152.0763 4244.626)
    ))
    ; P2994 -- see feature_dimensions_mm.csv
    ("06_ORNAMENT" 1 (
      (12150.3817 3930.0305) (12152.0763 3926.8855) (12156.7023 3924.3359) (12163.0076 3922.6718) (12169.3282 3921.8015)
      (12174.0611 3921.2214) (12176.1679 3920.1527) (12175.4351 3917.9084) (12172.5038 3914.1527) (12168.6412 3909.084)
      (12165.3588 3903.4504) (12163.8931 3898.3664) (12164.916 3894.9466) (12168.3359 3893.9237) (12173.4198 3895.3893)
      (12179.0534 3898.6718) (12184.1221 3902.5191) (12187.8779 3905.4504) (12190.1221 3906.1832) (12191.1908 3904.0916)
      (12191.7863 3899.3588) (12192.6412 3893.0382) (12194.3053 3886.7328) (12196.855 3882.1069) (12200.0 3880.4122)
      (12203.145 3882.1069) (12205.6947 3886.7328) (12207.3588 3893.0382) (12208.2137 3899.3588) (12208.8092 3904.0916)
      (12209.8779 3906.1832) (12212.1221 3905.4504) (12215.8779 3902.5191) (12220.9466 3898.6718) (12226.5802 3895.3893)
      (12231.6641 3893.9237) (12235.084 3894.9466) (12236.1069 3898.3664) (12234.6412 3903.4504) (12231.3588 3909.084)
      (12227.4962 3914.1527) (12224.5649 3917.9084) (12223.8321 3920.1527) (12225.9389 3921.2214) (12230.6718 3921.8015)
      (12236.9924 3922.6718) (12243.2977 3924.3359) (12247.9237 3926.8855) (12249.6183 3930.0305) (12247.9237 3933.1756)
      (12243.2977 3935.7252) (12236.9924 3937.3893) (12230.6718 3938.2443) (12225.9389 3938.8397) (12223.8321 3939.9084)
      (12224.5649 3942.1527) (12227.4962 3945.9084) (12231.3588 3950.9771) (12234.6412 3956.6107) (12236.1069 3961.6947)
      (12235.084 3965.1145) (12231.6641 3966.1374) (12226.5802 3964.6718) (12220.9466 3961.3893) (12215.8779 3957.5267)
      (12212.1221 3954.5954) (12209.8779 3953.8626) (12208.8092 3955.9695) (12208.2137 3960.7023) (12207.3588 3967.0076)
      (12205.6947 3973.313) (12203.145 3977.9542) (12200.0 3979.6489) (12196.855 3977.9542) (12194.3053 3973.313)
      (12192.6412 3967.0076) (12191.7863 3960.7023) (12191.1908 3955.9695) (12190.1221 3953.8626) (12187.8779 3954.5954)
      (12184.1221 3957.5267) (12179.0534 3961.3893) (12173.4198 3964.6718) (12168.3359 3966.1374) (12164.916 3965.1145)
      (12163.8931 3961.6947) (12165.3588 3956.6107) (12168.6412 3950.9771) (12172.5038 3945.9084) (12175.4351 3942.1527)
      (12176.1679 3939.9084) (12174.0611 3938.8397) (12169.3282 3938.2443) (12163.0076 3937.3893) (12156.7023 3935.7252)
      (12152.0763 3933.1756)
    ))
    ; P2995 -- see feature_dimensions_mm.csv
    ("06_ORNAMENT" 1 (
      (12181.6794 5253.6947) (12200.0 5233.084) (12218.3206 5253.6947) (12200.0 5274.3053)
    ))
    ; P2996 -- see feature_dimensions_mm.csv
    ("06_ORNAMENT" 1 (
      (12181.6794 4942.2443) (12200.0 4921.6336) (12218.3206 4942.2443) (12200.0 4962.855)
    ))
    ; P2997 -- see feature_dimensions_mm.csv
    ("06_ORNAMENT" 1 (
      (12181.6794 4630.7939) (12200.0 4610.1832) (12218.3206 4630.7939) (12200.0 4651.4046)
    ))
    ; P2998 -- see feature_dimensions_mm.csv
    ("06_ORNAMENT" 1 (
      (12181.6794 4319.3435) (12200.0 4298.7328) (12218.3206 4319.3435) (12200.0 4339.9542)
    ))
    ; P2999 -- see feature_dimensions_mm.csv
    ("06_ORNAMENT" 1 (
      (12181.6794 4007.8931) (12200.0 3987.2824) (12218.3206 4007.8931) (12200.0 4028.5038)
    ))
    ; P3000 -- see feature_dimensions_mm.csv
    ("06_ORNAMENT" 1 (
      (12188.0916 5487.2824) (12188.9924 5482.7176) (12191.5725 5478.855) (12195.4504 5476.2748) (12200.0 5475.374)
      (12204.5496 5476.2748) (12208.4275 5478.855) (12211.0076 5482.7176) (12211.9084 5487.2824) (12211.0076 5491.8321)
      (12208.4275 5495.6947) (12204.5496 5498.2748) (12200.0 5499.1908) (12195.4504 5498.2748) (12191.5725 5495.6947)
      (12188.9924 5491.8321)
    ))
    ; P3001 -- see feature_dimensions_mm.csv
    ("06_ORNAMENT" 1 (
      (12188.0916 5175.8321) (12188.9924 5171.2672) (12191.5725 5167.4046) (12195.4504 5164.8244) (12200.0 5163.9237)
      (12204.5496 5164.8244) (12208.4275 5167.4046) (12211.0076 5171.2672) (12211.9084 5175.8321) (12211.0076 5180.3817)
      (12208.4275 5184.2443) (12204.5496 5186.8244) (12200.0 5187.7405) (12195.4504 5186.8244) (12191.5725 5184.2443)
      (12188.9924 5180.3817)
    ))
    ; P3002 -- see feature_dimensions_mm.csv
    ("06_ORNAMENT" 1 (
      (12188.0916 4864.3817) (12188.9924 4859.8168) (12191.5725 4855.9542) (12195.4504 4853.374) (12200.0 4852.4733)
      (12204.5496 4853.374) (12208.4275 4855.9542) (12211.0076 4859.8168) (12211.9084 4864.3817) (12211.0076 4868.9313)
      (12208.4275 4872.7939) (12204.5496 4875.374) (12200.0 4876.2901) (12195.4504 4875.374) (12191.5725 4872.7939)
      (12188.9924 4868.9313)
    ))
    ; P3003 -- see feature_dimensions_mm.csv
    ("06_ORNAMENT" 1 (
      (12188.0916 4552.9313) (12188.9924 4548.3664) (12191.5725 4544.5038) (12195.4504 4541.9237) (12200.0 4541.0229)
      (12204.5496 4541.9237) (12208.4275 4544.5038) (12211.0076 4548.3664) (12211.9084 4552.9313) (12211.0076 4557.4809)
      (12208.4275 4561.3435) (12204.5496 4563.9237) (12200.0 4564.8397) (12195.4504 4563.9237) (12191.5725 4561.3435)
      (12188.9924 4557.4809)
    ))
    ; P3004 -- see feature_dimensions_mm.csv
    ("06_ORNAMENT" 1 (
      (12188.0916 4241.4809) (12188.9924 4236.916) (12191.5725 4233.0534) (12195.4504 4230.4733) (12200.0 4229.5725)
      (12204.5496 4230.4733) (12208.4275 4233.0534) (12211.0076 4236.916) (12211.9084 4241.4809) (12211.0076 4246.0305)
      (12208.4275 4249.8931) (12204.5496 4252.4733) (12200.0 4253.3893) (12195.4504 4252.4733) (12191.5725 4249.8931)
      (12188.9924 4246.0305)
    ))
    ; P3005 -- see feature_dimensions_mm.csv
    ("06_ORNAMENT" 1 (
      (12188.0916 3930.0305) (12188.9924 3925.4656) (12191.5725 3921.6031) (12195.4504 3919.0229) (12200.0 3918.1221)
      (12204.5496 3919.0229) (12208.4275 3921.6031) (12211.0076 3925.4656) (12211.9084 3930.0305) (12211.0076 3934.5802)
      (12208.4275 3938.4427) (12204.5496 3941.0229) (12200.0 3941.9389) (12195.4504 3941.0229) (12191.5725 3938.4427)
      (12188.9924 3934.5802)
    ))
    ; P3006 -- see feature_dimensions_mm.csv
    ("06_ORNAMENT" 1 (
      (12190.2137 5827.8321) (12204.6107 5825.2214) (12195.7405 5834.5344) (12192.2901 5837.6641)
    ))
    ; P3007 -- see feature_dimensions_mm.csv
    ("06_ORNAMENT" 1 (
      (12228.2443 5331.5573) (12229.9389 5328.4122) (12234.5649 5325.8626) (12240.8702 5324.1985) (12247.1908 5323.3282)
      (12251.9237 5322.7481) (12254.0305 5321.6794) (12253.2977 5319.4351) (12250.3664 5315.6794) (12246.5038 5310.6107)
      (12243.2214 5304.9771) (12241.7557 5299.8931) (12242.7786 5296.4733) (12246.1985 5295.4504) (12251.2824 5296.916)
      (12256.916 5300.1985) (12261.9847 5304.0458) (12265.7405 5306.9771) (12267.9847 5307.7099) (12269.0534 5305.6183)
      (12269.6489 5300.8855) (12270.5038 5294.5649) (12272.1679 5288.2595) (12274.7176 5283.6336) (12277.8626 5281.9389)
      (12281.0076 5283.6336) (12283.5573 5288.2595) (12285.2214 5294.5649) (12286.0763 5300.8855) (12286.6718 5305.6183)
      (12287.7405 5307.7099) (12289.9847 5306.9771) (12293.7405 5304.0458) (12298.8092 5300.1985) (12304.4427 5296.916)
      (12309.5267 5295.4504) (12312.9466 5296.4733) (12313.9695 5299.8931) (12312.5038 5304.9771) (12309.2214 5310.6107)
      (12305.3588 5315.6794) (12302.4275 5319.4351) (12301.6947 5321.6794) (12303.8015 5322.7481) (12308.5344 5323.3282)
      (12314.855 5324.1985) (12321.1603 5325.8626) (12325.7863 5328.4122) (12327.4809 5331.5573) (12325.7863 5334.7023)
      (12321.1603 5337.2519) (12314.855 5338.916) (12308.5344 5339.771) (12303.8015 5340.3664) (12301.6947 5341.4351)
      (12302.4275 5343.6794) (12305.3588 5347.4351) (12309.2214 5352.5038) (12312.5038 5358.1374) (12313.9695 5363.2214)
      (12312.9466 5366.6412) (12309.5267 5367.6641) (12304.4427 5366.1985) (12298.8092 5362.916) (12293.7405 5359.0534)
      (12289.9847 5356.1221) (12287.7405 5355.3893) (12286.6718 5357.4962) (12286.0763 5362.229) (12285.2214 5368.5344)
      (12283.5573 5374.8397) (12281.0076 5379.4809) (12277.8626 5381.1756) (12274.7176 5379.4809) (12272.1679 5374.8397)
      (12270.5038 5368.5344) (12269.6489 5362.229) (12269.0534 5357.4962) (12267.9847 5355.3893) (12265.7405 5356.1221)
      (12261.9847 5359.0534) (12256.916 5362.916) (12251.2824 5366.1985) (12246.1985 5367.6641) (12242.7786 5366.6412)
      (12241.7557 5363.2214) (12243.2214 5358.1374) (12246.5038 5352.5038) (12250.3664 5347.4351) (12253.2977 5343.6794)
      (12254.0305 5341.4351) (12251.9237 5340.3664) (12247.1908 5339.771) (12240.8702 5338.916) (12234.5649 5337.2519)
      (12229.9389 5334.7023)
    ))
    ; P3008 -- see feature_dimensions_mm.csv
    ("06_ORNAMENT" 1 (
      (12228.2443 5020.1069) (12229.9389 5016.9618) (12234.5649 5014.4122) (12240.8702 5012.7481) (12247.1908 5011.8779)
      (12251.9237 5011.2977) (12254.0305 5010.229) (12253.2977 5007.9847) (12250.3664 5004.229) (12246.5038 4999.1603)
      (12243.2214 4993.5267) (12241.7557 4988.4427) (12242.7786 4985.0229) (12246.1985 4984.0) (12251.2824 4985.4656)
      (12256.916 4988.7481) (12261.9847 4992.5954) (12265.7405 4995.5267) (12267.9847 4996.2595) (12269.0534 4994.1679)
      (12269.6489 4989.4351) (12270.5038 4983.1145) (12272.1679 4976.8092) (12274.7176 4972.1832) (12277.8626 4970.4885)
      (12281.0076 4972.1832) (12283.5573 4976.8092) (12285.2214 4983.1145) (12286.0763 4989.4351) (12286.6718 4994.1679)
      (12287.7405 4996.2595) (12289.9847 4995.5267) (12293.7405 4992.5954) (12298.8092 4988.7481) (12304.4427 4985.4656)
      (12309.5267 4984.0) (12312.9466 4985.0229) (12313.9695 4988.4427) (12312.5038 4993.5267) (12309.2214 4999.1603)
      (12305.3588 5004.229) (12302.4275 5007.9847) (12301.6947 5010.229) (12303.8015 5011.2977) (12308.5344 5011.8779)
      (12314.855 5012.7481) (12321.1603 5014.4122) (12325.7863 5016.9618) (12327.4809 5020.1069) (12325.7863 5023.2519)
      (12321.1603 5025.8015) (12314.855 5027.4656) (12308.5344 5028.3206) (12303.8015 5028.916) (12301.6947 5029.9847)
      (12302.4275 5032.229) (12305.3588 5035.9847) (12309.2214 5041.0534) (12312.5038 5046.687) (12313.9695 5051.771)
      (12312.9466 5055.1908) (12309.5267 5056.2137) (12304.4427 5054.7481) (12298.8092 5051.4656) (12293.7405 5047.6031)
      (12289.9847 5044.6718) (12287.7405 5043.9389) (12286.6718 5046.0458) (12286.0763 5050.7786) (12285.2214 5057.084)
      (12283.5573 5063.3893) (12281.0076 5068.0305) (12277.8626 5069.7252) (12274.7176 5068.0305) (12272.1679 5063.3893)
      (12270.5038 5057.084) (12269.6489 5050.7786) (12269.0534 5046.0458) (12267.9847 5043.9389) (12265.7405 5044.6718)
      (12261.9847 5047.6031) (12256.916 5051.4656) (12251.2824 5054.7481) (12246.1985 5056.2137) (12242.7786 5055.1908)
      (12241.7557 5051.771) (12243.2214 5046.687) (12246.5038 5041.0534) (12250.3664 5035.9847) (12253.2977 5032.229)
      (12254.0305 5029.9847) (12251.9237 5028.916) (12247.1908 5028.3206) (12240.8702 5027.4656) (12234.5649 5025.8015)
      (12229.9389 5023.2519)
    ))
    ; P3009 -- see feature_dimensions_mm.csv
    ("06_ORNAMENT" 1 (
      (12228.2443 4708.6565) (12229.9389 4705.5115) (12234.5649 4702.9618) (12240.8702 4701.2977) (12247.1908 4700.4275)
      (12251.9237 4699.8473) (12254.0305 4698.7786) (12253.2977 4696.5344) (12250.3664 4692.7786) (12246.5038 4687.7099)
      (12243.2214 4682.0763) (12241.7557 4676.9924) (12242.7786 4673.5725) (12246.1985 4672.5496) (12251.2824 4674.0153)
      (12256.916 4677.2977) (12261.9847 4681.145) (12265.7405 4684.0763) (12267.9847 4684.8092) (12269.0534 4682.7176)
      (12269.6489 4677.9847) (12270.5038 4671.6641) (12272.1679 4665.3588) (12274.7176 4660.7328) (12277.8626 4659.0382)
      (12281.0076 4660.7328) (12283.5573 4665.3588) (12285.2214 4671.6641) (12286.0763 4677.9847) (12286.6718 4682.7176)
      (12287.7405 4684.8092) (12289.9847 4684.0763) (12293.7405 4681.145) (12298.8092 4677.2977) (12304.4427 4674.0153)
      (12309.5267 4672.5496) (12312.9466 4673.5725) (12313.9695 4676.9924) (12312.5038 4682.0763) (12309.2214 4687.7099)
      (12305.3588 4692.7786) (12302.4275 4696.5344) (12301.6947 4698.7786) (12303.8015 4699.8473) (12308.5344 4700.4275)
      (12314.855 4701.2977) (12321.1603 4702.9618) (12325.7863 4705.5115) (12327.4809 4708.6565) (12325.7863 4711.8015)
      (12321.1603 4714.3511) (12314.855 4716.0153) (12308.5344 4716.8702) (12303.8015 4717.4656) (12301.6947 4718.5344)
      (12302.4275 4720.7786) (12305.3588 4724.5344) (12309.2214 4729.6031) (12312.5038 4735.2366) (12313.9695 4740.3206)
      (12312.9466 4743.7405) (12309.5267 4744.7634) (12304.4427 4743.2977) (12298.8092 4740.0153) (12293.7405 4736.1527)
      (12289.9847 4733.2214) (12287.7405 4732.4885) (12286.6718 4734.5954) (12286.0763 4739.3282) (12285.2214 4745.6336)
      (12283.5573 4751.9389) (12281.0076 4756.5802) (12277.8626 4758.2748) (12274.7176 4756.5802) (12272.1679 4751.9389)
      (12270.5038 4745.6336) (12269.6489 4739.3282) (12269.0534 4734.5954) (12267.9847 4732.4885) (12265.7405 4733.2214)
      (12261.9847 4736.1527) (12256.916 4740.0153) (12251.2824 4743.2977) (12246.1985 4744.7634) (12242.7786 4743.7405)
      (12241.7557 4740.3206) (12243.2214 4735.2366) (12246.5038 4729.6031) (12250.3664 4724.5344) (12253.2977 4720.7786)
      (12254.0305 4718.5344) (12251.9237 4717.4656) (12247.1908 4716.8702) (12240.8702 4716.0153) (12234.5649 4714.3511)
      (12229.9389 4711.8015)
    ))
    ; P3010 -- see feature_dimensions_mm.csv
    ("06_ORNAMENT" 1 (
      (12228.2443 4085.7557) (12229.9389 4082.6107) (12234.5649 4080.0611) (12240.8702 4078.3969) (12247.1908 4077.5267)
      (12251.9237 4076.9466) (12254.0305 4075.8779) (12253.2977 4073.6336) (12250.3664 4069.8779) (12246.5038 4064.8092)
      (12243.2214 4059.1756) (12241.7557 4054.0916) (12242.7786 4050.6718) (12246.1985 4049.6489) (12251.2824 4051.1145)
      (12256.916 4054.3969) (12261.9847 4058.2595) (12265.7405 4061.1756) (12267.9847 4061.9084) (12269.0534 4059.8168)
      (12269.6489 4055.084) (12270.5038 4048.7634) (12272.1679 4042.458) (12274.7176 4037.8321) (12277.8626 4036.1374)
      (12281.0076 4037.8321) (12283.5573 4042.458) (12285.2214 4048.7634) (12286.0763 4055.084) (12286.6718 4059.8168)
      (12287.7405 4061.9084) (12289.9847 4061.1756) (12293.7405 4058.2595) (12298.8092 4054.3969) (12304.4427 4051.1145)
      (12309.5267 4049.6489) (12312.9466 4050.6718) (12313.9695 4054.0916) (12312.5038 4059.1756) (12309.2214 4064.8092)
      (12305.3588 4069.8779) (12302.4275 4073.6336) (12301.6947 4075.8779) (12303.8015 4076.9466) (12308.5344 4077.5267)
      (12314.855 4078.3969) (12321.1603 4080.0611) (12325.7863 4082.6107) (12327.4809 4085.7557) (12325.7863 4088.9008)
      (12321.1603 4091.4504) (12314.855 4093.1145) (12308.5344 4093.9695) (12303.8015 4094.5649) (12301.6947 4095.6336)
      (12302.4275 4097.8779) (12305.3588 4101.6336) (12309.2214 4106.7023) (12312.5038 4112.3359) (12313.9695 4117.4198)
      (12312.9466 4120.8397) (12309.5267 4121.8626) (12304.4427 4120.3969) (12298.8092 4117.1145) (12293.7405 4113.2519)
      (12289.9847 4110.3206) (12287.7405 4109.5878) (12286.6718 4111.6947) (12286.0763 4116.4275) (12285.2214 4122.7328)
      (12283.5573 4129.0382) (12281.0076 4133.6794) (12277.8626 4135.374) (12274.7176 4133.6794) (12272.1679 4129.0382)
      (12270.5038 4122.7328) (12269.6489 4116.4275) (12269.0534 4111.6947) (12267.9847 4109.5878) (12265.7405 4110.3206)
      (12261.9847 4113.2519) (12256.916 4117.1145) (12251.2824 4120.3969) (12246.1985 4121.8626) (12242.7786 4120.8397)
      (12241.7557 4117.4198) (12243.2214 4112.3359) (12246.5038 4106.7023) (12250.3664 4101.6336) (12253.2977 4097.8779)
      (12254.0305 4095.6336) (12251.9237 4094.5649) (12247.1908 4093.9695) (12240.8702 4093.1145) (12234.5649 4091.4504)
      (12229.9389 4088.9008)
    ))
    ; P3011 -- see feature_dimensions_mm.csv
    ("06_ORNAMENT" 1 (
      (12239.4504 5898.3053) (12244.5802 5877.084) (12252.5191 5856.7023) (12262.9618 5837.2824) (12275.5878 5818.9313)
      (12282.9008 5810.229) (12325.9847 5801.2061) (12326.6718 5801.0534) (12377.0992 5789.6794) (12377.8321 5789.4962)
      (12422.8092 5778.5649) (12417.0076 5787.6794) (12404.0 5805.313) (12389.5725 5822.2443) (12373.8779 5838.1832)
      (12357.0229 5852.8702) (12339.1756 5866.0) (12320.4427 5877.2824) (12300.9618 5886.4427) (12299.4809 5886.9313)
      (12303.8015 5886.7023) (12326.0458 5887.9695) (12348.2748 5891.4198) (12370.229 5896.855) (12391.6489 5904.0458)
      (12412.2901 5912.7786) (12431.9237 5922.8397) (12450.2595 5934.0153) (12467.084 5946.0763) (12482.1069 5958.8092)
      (12495.1145 5972.0) (12498.5954 5976.3511) (12509.8168 5972.9771) (12523.7557 5970.4885) (12535.7557 5968.9618)
      (12544.3511 5967.2824) (12548.8092 5964.2748) (12549.1908 5958.916) (12546.3359 5950.626) (12541.6641 5939.4656)
      (12536.8397 5926.1527) (12533.5115 5912.0) (12532.916 5898.6565) (12535.7405 5887.8321) (12536.0458 5887.5115)
      (12522.3817 5881.9084) (12503.8321 5871.6794) (12486.9618 5859.2672) (12472.0458 5844.6107) (12472.9313 5822.7786)
      (12476.7481 5801.2519) (12483.1908 5780.1679) (12491.6947 5760.4122) (12534.8092 5748.1679) (12535.8015 5747.8779)
      (12587.3435 5731.9695) (12588.458 5731.6031) (12614.4122 5722.8702) (12604.458 5740.7023) (12592.1679 5759.4198)
      (12578.5038 5777.0992) (12563.542 5793.4504) (12547.374 5808.1832) (12530.0611 5820.9618) (12528.7176 5821.7405)
      (12532.9008 5820.6718) (12554.9618 5817.5725) (12577.4351 5816.6107) (12600.0153 5817.6641) (12622.4427 5820.5344)
      (12644.3969 5825.084) (12665.6031 5831.1298) (12685.771 5838.5038) (12704.626 5847.0534) (12721.8473 5856.6107)
      (12737.1756 5866.9924) (12750.3053 5878.0763) (12733.2977 5885.5115) (12714.6565 5891.8321) (12694.6565 5896.9008)
      (12688.2901 5898.0305) (12688.458 5898.6565) (12687.8626 5912.0) (12684.5344 5926.1527) (12679.7099 5939.4656)
      (12675.0382 5950.626) (12672.1832 5958.916) (12672.5649 5964.2748) (12677.0229 5967.2824) (12685.6183 5968.9618)
      (12697.6183 5970.4885) (12711.5573 5972.9771) (12725.4809 5977.1603) (12737.3435 5983.3282) (12745.2977 5991.1756)
      (12748.0916 6000.0) (12745.2977 6008.8244) (12737.3435 6016.6718) (12725.4809 6022.8397) (12711.5573 6027.0229)
      (12697.6183 6029.5115) (12685.6183 6031.0382) (12677.0229 6032.7176) (12672.5649 6035.7252) (12672.1832 6041.084)
      (12675.0382 6049.374) (12679.7099 6060.5344) (12684.5344 6073.8473) (12687.8626 6088.0) (12688.458 6101.3435)
      (12685.6336 6112.1679) (12679.3893 6118.9924) (12670.3511 6120.9771) (12659.5725 6118.0153) (12648.3053 6110.8397)
      (12637.7099 6100.8702) (12628.5954 6090.0458) (12621.2672 6080.4122) (12615.5267 6073.8015) (12610.687 6071.4504)
      (12605.8473 6073.8015) (12600.1069 6080.4122) (12592.7786 6090.0458) (12583.6641 6100.8702) (12573.0687 6110.8397)
      (12561.8015 6118.0153) (12551.0229 6120.9771) (12541.9847 6118.9924) (12535.7405 6112.1679) (12532.916 6101.3435)
      (12533.5115 6088.0) (12536.8397 6073.8473) (12541.6641 6060.5344) (12546.3359 6049.374) (12549.1908 6041.084)
      (12548.8092 6035.7252) (12544.3511 6032.7176) (12535.7557 6031.0382) (12523.7557 6029.5115) (12509.8168 6027.0229)
      (12495.8931 6022.8397) (12484.0305 6016.6718) (12476.0763 6008.8244) (12473.2824 6000.0) (12476.0763 5991.1756)
      (12476.3817 5990.8855) (12468.1832 5991.9542) (12447.5725 5993.0229) (12426.1985 5992.6107) (12404.3817 5990.6412)
      (12382.4275 5987.0992) (12360.6412 5981.9695) (12339.3435 5975.1908) (12318.855 5966.7481) (12299.4809 5956.5954)
      (12281.542 5944.7176) (12265.3435 5931.0687) (12251.2061 5915.6031)
    ))
    ; P3012 -- see feature_dimensions_mm.csv
    ("06_ORNAMENT" 1 (
      (12244.5496 1851.9542) (12245.2366 1851.2824) (12254.1679 1844.0611) (12263.9084 1837.3893) (12274.3359 1831.4046)
      (12285.3435 1826.1985) (12296.7634 1821.9084) (12308.4885 1818.6565) (12320.3969 1816.5496) (12332.3359 1815.6947)
      (12344.1832 1816.2443) (12355.8015 1818.2901) (12367.0687 1821.9695) (12377.8626 1827.3893) (12370.6107 1837.6336)
      (12362.1374 1846.6107) (12352.6107 1854.3206) (12342.2137 1860.8244) (12331.1145 1866.1527) (12319.5267 1870.3359)
      (12307.6031 1873.4198) (12295.542 1875.4198) (12283.5267 1876.3969) (12271.7252 1876.3511) (12260.3206 1875.3588)
      (12249.5115 1873.4198) (12245.2519 1872.2137)
    ))
    ; P3013 -- see feature_dimensions_mm.csv
    ("06_ORNAMENT" 1 (
      (12259.542 5409.4198) (12277.8626 5388.8092) (12296.1832 5409.4198) (12277.8626 5430.0305)
    ))
    ; P3014 -- see feature_dimensions_mm.csv
    ("06_ORNAMENT" 1 (
      (12259.542 5097.9695) (12277.8626 5077.3588) (12296.1832 5097.9695) (12277.8626 5118.5802)
    ))
    ; P3015 -- see feature_dimensions_mm.csv
    ("06_ORNAMENT" 1 (
      (12259.542 4786.5191) (12277.8626 4765.9084) (12296.1832 4786.5191) (12277.8626 4807.1298)
    ))
    ; P3016 -- see feature_dimensions_mm.csv
    ("06_ORNAMENT" 1 (
      (12259.542 4163.6183) (12277.8626 4143.0076) (12296.1832 4163.6183) (12277.8626 4184.229)
    ))
    ; P3017 -- see feature_dimensions_mm.csv
    ("06_ORNAMENT" 1 (
      (12259.542 3852.1679) (12277.4198 3832.0611) (12278.3053 3832.0611) (12296.1832 3852.1679) (12277.8626 3872.7786)
    ))
    ; P3018 -- see feature_dimensions_mm.csv
    ("06_ORNAMENT" 1 (
      (12265.9542 5331.5573) (12266.855 5326.9924) (12269.4351 5323.1298) (12273.313 5320.5496) (12277.8626 5319.6489)
      (12282.4122 5320.5496) (12286.2901 5323.1298) (12288.8702 5326.9924) (12289.771 5331.5573) (12288.8702 5336.1069)
      (12286.2901 5339.9695) (12282.4122 5342.5496) (12277.8626 5343.4656) (12273.313 5342.5496) (12269.4351 5339.9695)
      (12266.855 5336.1069)
    ))
    ; P3019 -- see feature_dimensions_mm.csv
    ("06_ORNAMENT" 1 (
      (12265.9542 5020.1069) (12266.855 5015.542) (12269.4351 5011.6794) (12273.313 5009.0992) (12277.8626 5008.1985)
      (12282.4122 5009.0992) (12286.2901 5011.6794) (12288.8702 5015.542) (12289.771 5020.1069) (12288.8702 5024.6565)
      (12286.2901 5028.5191) (12282.4122 5031.0992) (12277.8626 5032.0153) (12273.313 5031.0992) (12269.4351 5028.5191)
      (12266.855 5024.6565)
    ))
    ; P3020 -- see feature_dimensions_mm.csv
    ("06_ORNAMENT" 1 (
      (12265.9542 4708.6565) (12266.855 4704.0916) (12269.4351 4700.229) (12273.313 4697.6489) (12277.8626 4696.7481)
      (12282.4122 4697.6489) (12286.2901 4700.229) (12288.8702 4704.0916) (12289.771 4708.6565) (12288.8702 4713.2061)
      (12286.2901 4717.0687) (12282.4122 4719.6489) (12277.8626 4720.5649) (12273.313 4719.6489) (12269.4351 4717.0687)
      (12266.855 4713.2061)
    ))
    ; P3021 -- see feature_dimensions_mm.csv
    ("06_ORNAMENT" 1 (
      (12265.9542 4397.2061) (12266.855 4392.6412) (12269.4351 4388.7786) (12273.313 4386.1985) (12277.8626 4385.2977)
      (12282.4122 4386.1985) (12286.2901 4388.7786) (12288.8702 4392.6412) (12289.771 4397.2061) (12288.8702 4401.7557)
      (12286.2901 4405.6183) (12282.4122 4408.1985) (12277.8626 4409.1145) (12273.313 4408.1985) (12269.4351 4405.6183)
      (12266.855 4401.7557)
    ))
    ; P3022 -- see feature_dimensions_mm.csv
    ("06_ORNAMENT" 1 (
      (12265.9542 4085.7557) (12266.855 4081.1908) (12269.4351 4077.3282) (12273.313 4074.7481) (12277.8626 4073.8473)
      (12282.4122 4074.7481) (12286.2901 4077.3282) (12288.8702 4081.1908) (12289.771 4085.7557) (12288.8702 4090.3053)
      (12286.2901 4094.1679) (12282.4122 4096.7481) (12277.8626 4097.6641) (12273.313 4096.7481) (12269.4351 4094.1679)
      (12266.855 4090.3053)
    ))
    ; P3023 -- see feature_dimensions_mm.csv
    ("06_ORNAMENT" 1 (
      (12306.1069 5175.8321) (12307.8015 5172.687) (12312.4275 5170.1374) (12318.7328 5168.4733) (12325.0534 5167.6031)
      (12329.7863 5167.0229) (12331.8931 5165.9542) (12331.1603 5163.7099) (12328.229 5159.9542) (12324.3664 5154.8855)
      (12321.084 5149.2519) (12319.6183 5144.1679) (12320.6412 5140.7481) (12324.0611 5139.7252) (12329.145 5141.1908)
      (12334.7786 5144.4733) (12339.8473 5148.3206) (12343.6031 5151.2519) (12345.8473 5151.9847) (12346.916 5149.8931)
      (12347.5115 5145.1603) (12348.3664 5138.8397) (12350.0305 5132.5344) (12352.5802 5127.9084) (12355.7252 5126.2137)
      (12358.8702 5127.9084) (12361.4198 5132.5344) (12363.084 5138.8397) (12363.9389 5145.1603) (12364.5344 5149.8931)
      (12365.6031 5151.9847) (12367.8473 5151.2519) (12371.6031 5148.3206) (12376.6718 5144.4733) (12382.3053 5141.1908)
      (12387.3893 5139.7252) (12390.8092 5140.7481) (12391.8321 5144.1679) (12390.3664 5149.2519) (12387.084 5154.8855)
      (12383.2214 5159.9542) (12380.2901 5163.7099) (12379.5573 5165.9542) (12381.6641 5167.0229) (12386.3969 5167.6031)
      (12392.7176 5168.4733) (12399.0229 5170.1374) (12403.6489 5172.687) (12405.3435 5175.8321) (12403.6489 5178.9771)
      (12399.0229 5181.5267) (12392.7176 5183.1908) (12386.3969 5184.0458) (12381.6641 5184.6412) (12379.5573 5185.7099)
      (12380.2901 5187.9542) (12383.2214 5191.7099) (12387.084 5196.7786) (12390.3664 5202.4122) (12391.8321 5207.4962)
      (12390.8092 5210.916) (12387.3893 5211.9389) (12382.3053 5210.4733) (12376.6718 5207.1908) (12371.6031 5203.3282)
      (12367.8473 5200.3969) (12365.6031 5199.6641) (12364.5344 5201.771) (12363.9389 5206.5038) (12363.084 5212.8092)
      (12361.4198 5219.1145) (12358.8702 5223.7557) (12355.7252 5225.4504) (12352.5802 5223.7557) (12350.0305 5219.1145)
      (12348.3664 5212.8092) (12347.5115 5206.5038) (12346.916 5201.771) (12345.8473 5199.6641) (12343.6031 5200.3969)
      (12339.8473 5203.3282) (12334.7786 5207.1908) (12329.145 5210.4733) (12324.0611 5211.9389) (12320.6412 5210.916)
      (12319.6183 5207.4962) (12321.084 5202.4122) (12324.3664 5196.7786) (12328.229 5191.7099) (12331.1603 5187.9542)
      (12331.8931 5185.7099) (12329.7863 5184.6412) (12325.0534 5184.0458) (12318.7328 5183.1908) (12312.4275 5181.5267)
      (12307.8015 5178.9771)
    ))
    ; P3024 -- see feature_dimensions_mm.csv
    ("06_ORNAMENT" 1 (
      (12306.1069 4864.3817) (12307.8015 4861.2366) (12312.4275 4858.687) (12318.7328 4857.0229) (12325.0534 4856.1527)
      (12329.7863 4855.5725) (12331.8931 4854.5038) (12331.1603 4852.2595) (12328.229 4848.5038) (12324.3664 4843.4351)
      (12321.084 4837.8015) (12319.6183 4832.7176) (12320.6412 4829.2977) (12324.0611 4828.2748) (12329.145 4829.7405)
      (12334.7786 4833.0229) (12339.8473 4836.8702) (12343.6031 4839.8015) (12345.8473 4840.5344) (12346.916 4838.4427)
      (12347.5115 4833.7099) (12348.3664 4827.3893) (12350.0305 4821.084) (12352.5802 4816.458) (12355.7252 4814.7634)
      (12358.8702 4816.458) (12361.4198 4821.084) (12363.084 4827.3893) (12363.9389 4833.7099) (12364.5344 4838.4427)
      (12365.6031 4840.5344) (12367.8473 4839.8015) (12371.6031 4836.8702) (12376.6718 4833.0229) (12382.3053 4829.7405)
      (12387.3893 4828.2748) (12390.8092 4829.2977) (12391.8321 4832.7176) (12390.3664 4837.8015) (12387.084 4843.4351)
      (12383.2214 4848.5038) (12380.2901 4852.2595) (12379.5573 4854.5038) (12381.6641 4855.5725) (12386.3969 4856.1527)
      (12392.7176 4857.0229) (12399.0229 4858.687) (12403.6489 4861.2366) (12405.3435 4864.3817) (12403.6489 4867.5267)
      (12399.0229 4870.0763) (12392.7176 4871.7405) (12386.3969 4872.5954) (12381.6641 4873.1908) (12379.5573 4874.2595)
      (12380.2901 4876.5038) (12383.2214 4880.2595) (12387.084 4885.3282) (12390.3664 4890.9618) (12391.8321 4896.0458)
      (12390.8092 4899.4656) (12387.3893 4900.4885) (12382.3053 4899.0229) (12376.6718 4895.7405) (12371.6031 4891.8779)
      (12367.8473 4888.9466) (12365.6031 4888.2137) (12364.5344 4890.3206) (12363.9389 4895.0534) (12363.084 4901.3588)
      (12361.4198 4907.6641) (12358.8702 4912.3053) (12355.7252 4914.0) (12352.5802 4912.3053) (12350.0305 4907.6641)
      (12348.3664 4901.3588) (12347.5115 4895.0534) (12346.916 4890.3206) (12345.8473 4888.2137) (12343.6031 4888.9466)
      (12339.8473 4891.8779) (12334.7786 4895.7405) (12329.145 4899.0229) (12324.0611 4900.4885) (12320.6412 4899.4656)
      (12319.6183 4896.0458) (12321.084 4890.9618) (12324.3664 4885.3282) (12328.229 4880.2595) (12331.1603 4876.5038)
      (12331.8931 4874.2595) (12329.7863 4873.1908) (12325.0534 4872.5954) (12318.7328 4871.7405) (12312.4275 4870.0763)
      (12307.8015 4867.5267)
    ))
    ; P3025 -- see feature_dimensions_mm.csv
    ("06_ORNAMENT" 1 (
      (12306.1069 4552.9313) (12307.8015 4549.7863) (12312.4275 4547.2366) (12318.7328 4545.5725) (12325.0534 4544.7023)
      (12329.7863 4544.1221) (12331.8931 4543.0534) (12331.1603 4540.8092) (12328.229 4537.0534) (12324.3664 4531.9847)
      (12321.084 4526.3511) (12319.6183 4521.2672) (12320.6412 4517.8473) (12324.0611 4516.8244) (12329.145 4518.2901)
      (12334.7786 4521.5725) (12339.8473 4525.4198) (12343.6031 4528.3511) (12345.8473 4529.084) (12346.916 4526.9924)
      (12347.5115 4522.2595) (12348.3664 4515.9389) (12350.0305 4509.6336) (12352.5802 4505.0076) (12355.7252 4503.313)
      (12358.8702 4505.0076) (12361.4198 4509.6336) (12363.084 4515.9389) (12363.9389 4522.2595) (12364.5344 4526.9924)
      (12365.6031 4529.084) (12367.8473 4528.3511) (12371.6031 4525.4198) (12376.6718 4521.5725) (12382.3053 4518.2901)
      (12387.3893 4516.8244) (12390.8092 4517.8473) (12391.8321 4521.2672) (12390.3664 4526.3511) (12387.084 4531.9847)
      (12383.2214 4537.0534) (12380.2901 4540.8092) (12379.5573 4543.0534) (12381.6641 4544.1221) (12386.3969 4544.7023)
      (12392.7176 4545.5725) (12399.0229 4547.2366) (12403.6489 4549.7863) (12405.3435 4552.9313) (12403.6489 4556.0763)
      (12399.0229 4558.626) (12392.7176 4560.2901) (12386.3969 4561.145) (12381.6641 4561.7405) (12379.5573 4562.8092)
      (12380.2901 4565.0534) (12383.2214 4568.8092) (12387.084 4573.8779) (12390.3664 4579.5115) (12391.8321 4584.5954)
      (12390.8092 4588.0153) (12387.3893 4589.0382) (12382.3053 4587.5725) (12376.6718 4584.2901) (12371.6031 4580.4275)
      (12367.8473 4577.4962) (12365.6031 4576.7634) (12364.5344 4578.8702) (12363.9389 4583.6031) (12363.084 4589.9084)
      (12361.4198 4596.2137) (12358.8702 4600.855) (12355.7252 4602.5496) (12352.5802 4600.855) (12350.0305 4596.2137)
      (12348.3664 4589.9084) (12347.5115 4583.6031) (12346.916 4578.8702) (12345.8473 4576.7634) (12343.6031 4577.4962)
      (12339.8473 4580.4275) (12334.7786 4584.2901) (12329.145 4587.5725) (12324.0611 4589.0382) (12320.6412 4588.0153)
      (12319.6183 4584.5954) (12321.084 4579.5115) (12324.3664 4573.8779) (12328.229 4568.8092) (12331.1603 4565.0534)
      (12331.8931 4562.8092) (12329.7863 4561.7405) (12325.0534 4561.145) (12318.7328 4560.2901) (12312.4275 4558.626)
      (12307.8015 4556.0763)
    ))
    ; P3026 -- see feature_dimensions_mm.csv
    ("06_ORNAMENT" 1 (
      (12306.1069 4241.4809) (12307.8015 4238.3359) (12312.4275 4235.7863) (12318.7328 4234.1221) (12325.0534 4233.2519)
      (12329.7863 4232.6718) (12331.8931 4231.6031) (12331.1603 4229.3588) (12328.229 4225.6031) (12324.3664 4220.5344)
      (12321.084 4214.9008) (12319.6183 4209.8168) (12320.6412 4206.3969) (12324.0611 4205.374) (12329.145 4206.8397)
      (12334.7786 4210.1221) (12339.8473 4213.9695) (12343.6031 4216.9008) (12345.8473 4217.6336) (12346.916 4215.542)
      (12347.5115 4210.8092) (12348.3664 4204.4885) (12350.0305 4198.1832) (12352.5802 4193.5573) (12355.7252 4191.8626)
      (12358.8702 4193.5573) (12361.4198 4198.1832) (12363.084 4204.4885) (12363.9389 4210.8092) (12364.5344 4215.542)
      (12365.6031 4217.6336) (12367.8473 4216.9008) (12371.6031 4213.9695) (12376.6718 4210.1221) (12382.3053 4206.8397)
      (12387.3893 4205.374) (12390.8092 4206.3969) (12391.8321 4209.8168) (12390.3664 4214.9008) (12387.084 4220.5344)
      (12383.2214 4225.6031) (12380.2901 4229.3588) (12379.5573 4231.6031) (12381.6641 4232.6718) (12386.3969 4233.2519)
      (12392.7176 4234.1221) (12399.0229 4235.7863) (12403.6489 4238.3359) (12405.3435 4241.4809) (12403.6489 4244.626)
      (12399.0229 4247.1756) (12392.7176 4248.8397) (12386.3969 4249.6947) (12381.6641 4250.2901) (12379.5573 4251.3588)
      (12380.2901 4253.6031) (12383.2214 4257.3588) (12387.084 4262.4275) (12390.3664 4268.0611) (12391.8321 4273.145)
      (12390.8092 4276.5649) (12387.3893 4277.5878) (12382.3053 4276.1221) (12376.6718 4272.8397) (12371.6031 4268.9771)
      (12367.8473 4266.0458) (12365.6031 4265.313) (12364.5344 4267.4198) (12363.9389 4272.1527) (12363.084 4278.458)
      (12361.4198 4284.7634) (12358.8702 4289.4046) (12355.7252 4291.0992) (12352.5802 4289.4046) (12350.0305 4284.7634)
      (12348.3664 4278.458) (12347.5115 4272.1527) (12346.916 4267.4198) (12345.8473 4265.313) (12343.6031 4266.0458)
      (12339.8473 4268.9771) (12334.7786 4272.8397) (12329.145 4276.1221) (12324.0611 4277.5878) (12320.6412 4276.5649)
      (12319.6183 4273.145) (12321.084 4268.0611) (12324.3664 4262.4275) (12328.229 4257.3588) (12331.1603 4253.6031)
      (12331.8931 4251.3588) (12329.7863 4250.2901) (12325.0534 4249.6947) (12318.7328 4248.8397) (12312.4275 4247.1756)
      (12307.8015 4244.626)
    ))
    ; P3027 -- see feature_dimensions_mm.csv
    ("06_ORNAMENT" 1 (
      (12306.1069 3930.0305) (12307.8015 3926.8855) (12312.4275 3924.3359) (12318.7328 3922.6718) (12325.0534 3921.8015)
      (12329.7863 3921.2214) (12331.8931 3920.1527) (12331.1603 3917.9084) (12328.229 3914.1527) (12324.3664 3909.084)
      (12321.084 3903.4504) (12319.6183 3898.3664) (12320.6412 3894.9466) (12324.0611 3893.9237) (12329.145 3895.3893)
      (12334.7786 3898.6718) (12339.8473 3902.5191) (12343.6031 3905.4504) (12345.8473 3906.1832) (12346.916 3904.0916)
      (12347.5115 3899.3588) (12348.3664 3893.0382) (12350.0305 3886.7328) (12352.5802 3882.1069) (12355.7252 3880.4122)
      (12358.8702 3882.1069) (12361.4198 3886.7328) (12363.084 3893.0382) (12363.9389 3899.3588) (12364.5344 3904.0916)
      (12365.6031 3906.1832) (12367.8473 3905.4504) (12371.6031 3902.5191) (12376.6718 3898.6718) (12382.3053 3895.3893)
      (12387.3893 3893.9237) (12390.8092 3894.9466) (12391.8321 3898.3664) (12390.3664 3903.4504) (12387.084 3909.084)
      (12383.2214 3914.1527) (12380.2901 3917.9084) (12379.5573 3920.1527) (12381.6641 3921.2214) (12386.3969 3921.8015)
      (12392.7176 3922.6718) (12399.0229 3924.3359) (12403.6489 3926.8855) (12405.3435 3930.0305) (12403.6489 3933.1756)
      (12399.0229 3935.7252) (12392.7176 3937.3893) (12386.3969 3938.2443) (12381.6641 3938.8397) (12379.5573 3939.9084)
      (12380.2901 3942.1527) (12383.2214 3945.9084) (12387.084 3950.9771) (12390.3664 3956.6107) (12391.8321 3961.6947)
      (12390.8092 3965.1145) (12387.3893 3966.1374) (12382.3053 3964.6718) (12376.6718 3961.3893) (12371.6031 3957.5267)
      (12367.8473 3954.5954) (12365.6031 3953.8626) (12364.5344 3955.9695) (12363.9389 3960.7023) (12363.084 3967.0076)
      (12361.4198 3973.313) (12358.8702 3977.9542) (12355.7252 3979.6489) (12352.5802 3977.9542) (12350.0305 3973.313)
      (12348.3664 3967.0076) (12347.5115 3960.7023) (12346.916 3955.9695) (12345.8473 3953.8626) (12343.6031 3954.5954)
      (12339.8473 3957.5267) (12334.7786 3961.3893) (12329.145 3964.6718) (12324.0611 3966.1374) (12320.6412 3965.1145)
      (12319.6183 3961.6947) (12321.084 3956.6107) (12324.3664 3950.9771) (12328.229 3945.9084) (12331.1603 3942.1527)
      (12331.8931 3939.9084) (12329.7863 3938.8397) (12325.0534 3938.2443) (12318.7328 3937.3893) (12312.4275 3935.7252)
      (12307.8015 3933.1756)
    ))
    ; P3028 -- see feature_dimensions_mm.csv
    ("06_ORNAMENT" 1 (
      (12320.6107 1740.458) (12335.4198 1731.4656) (12351.8779 1723.374) (12369.7099 1716.2901) (12388.6412 1710.3511)
      (12408.4122 1705.6641) (12428.7634 1702.3511) (12449.4046 1700.5496) (12470.1069 1700.3817) (12490.5649 1701.9695)
      (12510.5344 1705.4198) (12529.7557 1710.8702) (12547.9389 1718.4427) (12564.8244 1728.2748) (12580.1527 1740.458)
      (12563.7557 1752.6412) (12545.8931 1762.4733) (12526.8397 1770.0458) (12506.9008 1775.4962) (12486.3511 1778.9466)
      (12465.4656 1780.5344) (12444.5496 1780.3664) (12423.8473 1778.5649) (12403.6794 1775.2519) (12384.3206 1770.5649)
      (12366.0458 1764.626) (12349.1603 1757.542) (12333.9084 1749.4504)
    ))
    ; P3029 -- see feature_dimensions_mm.csv
    ("06_ORNAMENT" 1 (
      (12337.4046 5253.6947) (12355.7252 5233.084) (12374.0458 5253.6947) (12355.7252 5274.3053)
    ))
    ; P3030 -- see feature_dimensions_mm.csv
    ("06_ORNAMENT" 1 (
      (12337.4046 4942.2443) (12355.7252 4921.6336) (12374.0458 4942.2443) (12355.7252 4962.855)
    ))
    ; P3031 -- see feature_dimensions_mm.csv
    ("06_ORNAMENT" 1 (
      (12337.4046 4630.7939) (12355.7252 4610.1832) (12374.0458 4630.7939) (12355.7252 4651.4046)
    ))
    ; P3032 -- see feature_dimensions_mm.csv
    ("06_ORNAMENT" 1 (
      (12337.4046 4319.3435) (12355.7252 4298.7328) (12374.0458 4319.3435) (12355.7252 4339.9542)
    ))
    ; P3033 -- see feature_dimensions_mm.csv
    ("06_ORNAMENT" 1 (
      (12337.4046 4007.8931) (12355.7252 3987.2824) (12374.0458 4007.8931) (12355.7252 4028.5038)
    ))
    ; P3034 -- see feature_dimensions_mm.csv
    ("06_ORNAMENT" 1 (
      (12343.8168 5487.2824) (12344.7176 5482.7176) (12347.2977 5478.855) (12351.1756 5476.2748) (12355.7252 5475.374)
      (12360.2748 5476.2748) (12364.1527 5478.855) (12366.7328 5482.7176) (12367.6336 5487.2824) (12366.7328 5491.8321)
      (12364.1527 5495.6947) (12360.2748 5498.2748) (12355.7252 5499.1908) (12351.1756 5498.2748) (12347.2977 5495.6947)
      (12344.7176 5491.8321)
    ))
    ; P3035 -- see feature_dimensions_mm.csv
    ("06_ORNAMENT" 1 (
      (12343.8168 5175.8321) (12344.7176 5171.2672) (12347.2977 5167.4046) (12351.1756 5164.8244) (12355.7252 5163.9237)
      (12360.2748 5164.8244) (12364.1527 5167.4046) (12366.7328 5171.2672) (12367.6336 5175.8321) (12366.7328 5180.3817)
      (12364.1527 5184.2443) (12360.2748 5186.8244) (12355.7252 5187.7405) (12351.1756 5186.8244) (12347.2977 5184.2443)
      (12344.7176 5180.3817)
    ))
    ; P3036 -- see feature_dimensions_mm.csv
    ("06_ORNAMENT" 1 (
      (12343.8168 4864.3817) (12344.7176 4859.8168) (12347.2977 4855.9542) (12351.1756 4853.374) (12355.7252 4852.4733)
      (12360.2748 4853.374) (12364.1527 4855.9542) (12366.7328 4859.8168) (12367.6336 4864.3817) (12366.7328 4868.9313)
      (12364.1527 4872.7939) (12360.2748 4875.374) (12355.7252 4876.2901) (12351.1756 4875.374) (12347.2977 4872.7939)
      (12344.7176 4868.9313)
    ))
    ; P3037 -- see feature_dimensions_mm.csv
    ("06_ORNAMENT" 1 (
      (12343.8168 4552.9313) (12344.7176 4548.3664) (12347.2977 4544.5038) (12351.1756 4541.9237) (12355.7252 4541.0229)
      (12360.2748 4541.9237) (12364.1527 4544.5038) (12366.7328 4548.3664) (12367.6336 4552.9313) (12366.7328 4557.4809)
      (12364.1527 4561.3435) (12360.2748 4563.9237) (12355.7252 4564.8397) (12351.1756 4563.9237) (12347.2977 4561.3435)
      (12344.7176 4557.4809)
    ))
    ; P3038 -- see feature_dimensions_mm.csv
    ("06_ORNAMENT" 1 (
      (12343.8168 4241.4809) (12344.7176 4236.916) (12347.2977 4233.0534) (12351.1756 4230.4733) (12355.7252 4229.5725)
      (12360.2748 4230.4733) (12364.1527 4233.0534) (12366.7328 4236.916) (12367.6336 4241.4809) (12366.7328 4246.0305)
      (12364.1527 4249.8931) (12360.2748 4252.4733) (12355.7252 4253.3893) (12351.1756 4252.4733) (12347.2977 4249.8931)
      (12344.7176 4246.0305)
    ))
    ; P3039 -- see feature_dimensions_mm.csv
    ("06_ORNAMENT" 1 (
      (12343.8168 3930.0305) (12344.7176 3925.4656) (12347.2977 3921.6031) (12351.1756 3919.0229) (12355.7252 3918.1221)
      (12360.2748 3919.0229) (12364.1527 3921.6031) (12366.7328 3925.4656) (12367.6336 3930.0305) (12366.7328 3934.5802)
      (12364.1527 3938.4427) (12360.2748 3941.0229) (12355.7252 3941.9389) (12351.1756 3941.0229) (12347.2977 3938.4427)
      (12344.7176 3934.5802)
    ))
    ; P3040 -- see feature_dimensions_mm.csv
    ("06_ORNAMENT" 1 (
      (12356.8397 2085.9084) (12358.8092 2075.5725) (12361.8779 2064.9618) (12366.0 2054.2443) (12371.0992 2043.6031)
      (12377.145 2033.1908) (12384.0763 2023.1908) (12391.8168 2013.7557) (12400.3511 2005.0687) (12409.6031 1997.2977)
      (12419.5115 1990.5954) (12430.0458 1985.145) (12441.145 1981.1145) (12452.7328 1978.6565) (12464.7939 1977.9542)
      (12463.6489 1990.458) (12460.7786 2002.458) (12456.3969 2013.9084) (12450.6412 2024.7481) (12443.6947 2034.9008)
      (12435.7557 2044.3206) (12426.9618 2052.9466) (12417.5267 2060.7176) (12407.5878 2067.5573) (12397.3588 2073.4351)
      (12386.9924 2078.2595) (12376.6565 2082.0) (12366.5496 2084.5649)
    ))
    ; P3041 -- see feature_dimensions_mm.csv
    ("06_ORNAMENT" 1 (
      (12356.8397 1395.0076) (12367.1756 1396.9771) (12377.7863 1400.0458) (12388.5038 1404.1679) (12399.145 1409.2672)
      (12408.3817 1414.6412) (12408.4427 1413.1603) (12409.9237 1406.8702) (12412.0763 1400.9466) (12414.1527 1395.9847)
      (12415.4198 1392.3053) (12415.2519 1389.9237) (12413.2672 1388.5802) (12409.4504 1387.8473) (12404.1069 1387.1603)
      (12397.9237 1386.0611) (12391.7252 1384.1985) (12386.458 1381.4504) (12382.916 1377.9695) (12381.6794 1374.0458)
      (12382.916 1370.1221) (12386.458 1366.6412) (12391.7252 1363.8931) (12397.9237 1362.0305) (12404.1069 1360.9313)
      (12409.4504 1360.2443) (12413.2672 1359.5115) (12415.2519 1358.1679) (12415.4198 1355.7863) (12414.1527 1352.1069)
      (12412.0763 1347.145) (12409.9237 1341.2214) (12408.4427 1334.9313) (12408.1832 1329.0076) (12409.4351 1324.1985)
      (12412.2137 1321.1603) (12416.229 1320.2748) (12421.0229 1321.5878) (12426.0305 1324.7786) (12430.7328 1329.2214)
      (12434.7939 1334.0305) (12438.0458 1338.3053) (12440.5954 1341.2519) (12442.7481 1342.2901) (12444.9008 1341.2519)
      (12447.4504 1338.3053) (12450.7023 1334.0305) (12454.7634 1329.2214) (12459.4656 1324.7786) (12464.4733 1321.5878)
      (12469.2672 1320.2748) (12473.2824 1321.1603) (12476.0611 1324.1985) (12477.313 1329.0076) (12477.0534 1334.9313)
      (12475.5725 1341.2214) (12473.4198 1347.145) (12471.3435 1352.1069) (12470.0763 1355.7863) (12470.2443 1358.1679)
      (12472.229 1359.5115) (12476.0458 1360.2443) (12481.3893 1360.9313) (12487.5725 1362.0305) (12493.771 1363.8931)
      (12499.0382 1366.6412) (12502.5802 1370.1221) (12503.8168 1374.0458) (12502.5802 1377.9695) (12499.0382 1381.4504)
      (12493.771 1384.1985) (12487.5725 1386.0611) (12481.3893 1387.1603) (12476.0458 1387.8473) (12472.229 1388.5802)
      (12470.2443 1389.9237) (12470.0763 1392.3053) (12471.3435 1395.9847) (12473.4198 1400.9466) (12475.5725 1406.8702)
      (12477.0534 1413.1603) (12477.313 1419.084) (12476.0611 1423.8931) (12473.2824 1426.9313) (12469.2672 1427.8168)
      (12464.4733 1426.5038) (12459.4656 1423.313) (12454.7634 1418.8702) (12450.7023 1414.0611) (12447.4504 1409.7863)
      (12444.9008 1406.8397) (12442.7481 1405.8015) (12440.5954 1406.8397) (12438.0458 1409.7863) (12434.7939 1414.0611)
      (12430.7328 1418.8702) (12426.0305 1423.313) (12423.1145 1425.1603) (12428.9924 1429.9847) (12437.6794 1438.5191)
      (12445.4504 1447.771) (12452.1527 1457.6794) (12457.6031 1468.2137) (12461.6336 1479.313) (12464.0916 1490.9008)
      (12464.7939 1502.9618) (12452.2901 1501.8168) (12440.2901 1498.9466) (12428.8397 1494.5649) (12418.0 1488.8092)
      (12407.8473 1481.8626) (12398.4275 1473.9237) (12389.8015 1465.1298) (12382.0305 1455.6947) (12375.1908 1445.7557)
      (12369.313 1435.5267) (12364.4885 1425.1603) (12360.7481 1414.8244) (12358.1832 1404.7176)
    ))
    ; P3042 -- see feature_dimensions_mm.csv
    ("06_ORNAMENT" 1 (
      (12371.7405 1931.2977) (12380.0763 1916.1069) (12390.2901 1900.8702) (12402.1832 1885.8168) (12415.6031 1871.2061)
      (12430.3817 1857.2672) (12446.3511 1844.229) (12463.3435 1832.3359) (12481.1756 1821.8473) (12499.6794 1812.9771)
      (12518.7023 1805.9847) (12538.0763 1801.1145) (12557.6031 1798.5802) (12577.145 1798.6412) (12596.5191 1801.5267)
      (12588.4122 1820.2748) (12577.8473 1837.7252) (12565.145 1853.8015) (12550.5954 1868.4885) (12534.5344 1881.771)
      (12517.2366 1893.5725) (12499.0229 1903.8931) (12480.2137 1912.6718) (12461.084 1919.8931) (12441.9847 1925.5115)
      (12423.1756 1929.5115) (12405.0076 1931.8168) (12387.7557 1932.4275)
    ))
    ; P3043 -- see feature_dimensions_mm.csv
    ("06_ORNAMENT" 1 (
      (12371.7405 1549.6183) (12389.0687 1549.2366) (12407.3588 1550.458) (12426.3511 1553.2366) (12445.7099 1557.5573)
      (12465.1756 1563.374) (12484.458 1570.687) (12503.2366 1579.4656) (12521.2519 1589.6641) (12538.1832 1601.2519)
      (12553.7405 1614.2443) (12567.6641 1628.5649) (12579.6183 1644.2137) (12589.3282 1661.1756) (12596.5191 1679.3893)
      (12576.2137 1681.7405) (12555.8321 1681.313) (12535.5573 1678.3511) (12515.5573 1673.1145) (12496.0305 1665.8321)
      (12477.1603 1656.7481) (12459.1145 1646.1374) (12442.1069 1634.2443) (12426.2901 1621.2977) (12411.8626 1607.5573)
      (12399.0229 1593.2672) (12387.9237 1578.687) (12378.7786 1564.0458)
    ))
    ; P3044 -- see feature_dimensions_mm.csv
    ("06_ORNAMENT" 1 (
      (12381.6794 2137.4046) (12382.916 2133.4809) (12386.458 2130.0) (12391.7252 2127.2519) (12397.9237 2125.3893)
      (12404.1069 2124.2901) (12409.4504 2123.6031) (12413.2672 2122.8702) (12415.2519 2121.5267) (12415.4198 2119.145)
      (12414.1527 2115.4656) (12412.0763 2110.5038) (12409.9237 2104.5802) (12408.4427 2098.2901) (12408.1832 2092.3664)
      (12409.4351 2087.5573) (12412.2137 2084.5191) (12416.229 2083.6336) (12421.0229 2084.9466) (12426.0305 2088.1374)
      (12430.7328 2092.5802) (12434.7939 2097.3893) (12438.0458 2101.6641) (12440.5954 2104.6107) (12442.7481 2105.6489)
      (12444.9008 2104.6107) (12447.4504 2101.6641) (12450.7023 2097.3893) (12454.7634 2092.5802) (12459.4656 2088.1374)
      (12464.4733 2084.9466) (12469.2672 2083.6336) (12473.2824 2084.5191) (12476.0611 2087.5573) (12477.313 2092.3664)
      (12477.0534 2098.2901) (12475.5725 2104.5802) (12473.4198 2110.5038) (12471.3435 2115.4656) (12470.0763 2119.145)
      (12470.2443 2121.5267) (12472.229 2122.8702) (12476.0458 2123.6031) (12481.3893 2124.2901) (12487.5725 2125.3893)
      (12493.771 2127.2519) (12499.0382 2130.0) (12502.5802 2133.4809) (12503.8168 2137.4046) (12502.5802 2141.3282)
      (12499.0382 2144.8092) (12493.771 2147.5573) (12487.5725 2149.4198) (12481.3893 2150.5191) (12476.0458 2151.2061)
      (12472.229 2151.9389) (12470.2443 2153.2824) (12470.0763 2155.6641) (12471.3435 2159.3435) (12473.4198 2164.3053)
      (12475.5725 2170.229) (12477.0534 2176.5191) (12477.313 2182.4427) (12476.0611 2187.2519) (12473.2824 2190.2901)
      (12469.2672 2191.1756) (12464.4733 2189.8626) (12459.4656 2186.6718) (12454.7634 2182.229) (12450.7023 2177.4198)
      (12447.4504 2173.145) (12444.9008 2170.1985) (12442.7481 2169.1603) (12440.5954 2170.1985) (12438.0458 2173.145)
      (12434.7939 2177.4198) (12430.7328 2182.229) (12426.0305 2186.6718) (12425.3435 2187.0992) (12423.4656 2185.8473)
      (12408.9008 2174.5954) (12409.9237 2170.229) (12412.0763 2164.3053) (12414.1527 2159.3435) (12415.4198 2155.6641)
      (12415.2519 2153.2824) (12413.2672 2151.9389) (12409.4504 2151.2061) (12404.1069 2150.5191) (12397.9237 2149.4198)
      (12391.7252 2147.5573) (12386.458 2144.8092) (12382.916 2141.3282)
    ))
    ; P3045 -- see feature_dimensions_mm.csv
    ("06_ORNAMENT" 1 (
      (12383.9695 5331.5573) (12385.6641 5328.4122) (12390.2901 5325.8626) (12396.5954 5324.1985) (12402.916 5323.3282)
      (12407.6489 5322.7481) (12409.7557 5321.6794) (12409.0229 5319.4351) (12406.0916 5315.6794) (12402.229 5310.6107)
      (12398.9466 5304.9771) (12397.4809 5299.8931) (12398.5038 5296.4733) (12401.9237 5295.4504) (12407.0076 5296.916)
      (12412.6412 5300.1985) (12417.7099 5304.0458) (12421.4656 5306.9771) (12423.7099 5307.7099) (12424.7786 5305.6183)
      (12425.374 5300.8855) (12426.229 5294.5649) (12427.8931 5288.2595) (12430.4427 5283.6336) (12433.5878 5281.9389)
      (12436.7328 5283.6336) (12439.2824 5288.2595) (12440.9466 5294.5649) (12441.8015 5300.8855) (12442.3969 5305.6183)
      (12443.4656 5307.7099) (12445.7099 5306.9771) (12449.4656 5304.0458) (12454.5344 5300.1985) (12460.1679 5296.916)
      (12465.2519 5295.4504) (12468.6718 5296.4733) (12469.6947 5299.8931) (12468.229 5304.9771) (12464.9466 5310.6107)
      (12461.084 5315.6794) (12458.1527 5319.4351) (12457.4198 5321.6794) (12459.5267 5322.7481) (12464.2595 5323.3282)
      (12470.5802 5324.1985) (12476.8855 5325.8626) (12481.5115 5328.4122) (12483.2061 5331.5573) (12481.5115 5334.7023)
      (12476.8855 5337.2519) (12470.5802 5338.916) (12464.2595 5339.771) (12459.5267 5340.3664) (12457.4198 5341.4351)
      (12458.1527 5343.6794) (12461.084 5347.4351) (12464.9466 5352.5038) (12468.229 5358.1374) (12469.6947 5363.2214)
      (12468.6718 5366.6412) (12465.2519 5367.6641) (12460.1679 5366.1985) (12454.5344 5362.916) (12449.4656 5359.0534)
      (12445.7099 5356.1221) (12443.4656 5355.3893) (12442.3969 5357.4962) (12441.8015 5362.229) (12440.9466 5368.5344)
      (12439.2824 5374.8397) (12436.7328 5379.4809) (12433.5878 5381.1756) (12430.4427 5379.4809) (12427.8931 5374.8397)
      (12426.229 5368.5344) (12425.374 5362.229) (12424.7786 5357.4962) (12423.7099 5355.3893) (12421.4656 5356.1221)
      (12417.7099 5359.0534) (12412.6412 5362.916) (12407.0076 5366.1985) (12401.9237 5367.6641) (12398.5038 5366.6412)
      (12397.4809 5363.2214) (12398.9466 5358.1374) (12402.229 5352.5038) (12406.0916 5347.4351) (12409.0229 5343.6794)
      (12409.7557 5341.4351) (12407.6489 5340.3664) (12402.916 5339.771) (12396.5954 5338.916) (12390.2901 5337.2519)
      (12385.6641 5334.7023)
    ))
    ; P3046 -- see feature_dimensions_mm.csv
    ("06_ORNAMENT" 1 (
      (12383.9695 5020.1069) (12385.6641 5016.9618) (12390.2901 5014.4122) (12396.5954 5012.7481) (12402.916 5011.8779)
      (12407.6489 5011.2977) (12409.7557 5010.229) (12409.0229 5007.9847) (12406.0916 5004.229) (12402.229 4999.1603)
      (12398.9466 4993.5267) (12397.4809 4988.4427) (12398.5038 4985.0229) (12401.9237 4984.0) (12407.0076 4985.4656)
      (12412.6412 4988.7481) (12417.7099 4992.5954) (12421.4656 4995.5267) (12423.7099 4996.2595) (12424.7786 4994.1679)
      (12425.374 4989.4351) (12426.229 4983.1145) (12427.8931 4976.8092) (12430.4427 4972.1832) (12433.5878 4970.4885)
      (12436.7328 4972.1832) (12439.2824 4976.8092) (12440.9466 4983.1145) (12441.8015 4989.4351) (12442.3969 4994.1679)
      (12443.4656 4996.2595) (12445.7099 4995.5267) (12449.4656 4992.5954) (12454.5344 4988.7481) (12460.1679 4985.4656)
      (12465.2519 4984.0) (12468.6718 4985.0229) (12469.6947 4988.4427) (12468.229 4993.5267) (12464.9466 4999.1603)
      (12461.084 5004.229) (12458.1527 5007.9847) (12457.4198 5010.229) (12459.5267 5011.2977) (12464.2595 5011.8779)
      (12470.5802 5012.7481) (12476.8855 5014.4122) (12481.5115 5016.9618) (12483.2061 5020.1069) (12481.5115 5023.2519)
      (12476.8855 5025.8015) (12470.5802 5027.4656) (12464.2595 5028.3206) (12459.5267 5028.916) (12457.4198 5029.9847)
      (12458.1527 5032.229) (12461.084 5035.9847) (12464.9466 5041.0534) (12468.229 5046.687) (12469.6947 5051.771)
      (12468.6718 5055.1908) (12465.2519 5056.2137) (12460.1679 5054.7481) (12454.5344 5051.4656) (12449.4656 5047.6031)
      (12445.7099 5044.6718) (12443.4656 5043.9389) (12442.3969 5046.0458) (12441.8015 5050.7786) (12440.9466 5057.084)
      (12439.2824 5063.3893) (12436.7328 5068.0305) (12433.5878 5069.7252) (12430.4427 5068.0305) (12427.8931 5063.3893)
      (12426.229 5057.084) (12425.374 5050.7786) (12424.7786 5046.0458) (12423.7099 5043.9389) (12421.4656 5044.6718)
      (12417.7099 5047.6031) (12412.6412 5051.4656) (12407.0076 5054.7481) (12401.9237 5056.2137) (12398.5038 5055.1908)
      (12397.4809 5051.771) (12398.9466 5046.687) (12402.229 5041.0534) (12406.0916 5035.9847) (12409.0229 5032.229)
      (12409.7557 5029.9847) (12407.6489 5028.916) (12402.916 5028.3206) (12396.5954 5027.4656) (12390.2901 5025.8015)
      (12385.6641 5023.2519)
    ))
    ; P3047 -- see feature_dimensions_mm.csv
    ("06_ORNAMENT" 1 (
      (12383.9695 4708.6565) (12385.6641 4705.5115) (12390.2901 4702.9618) (12396.5954 4701.2977) (12402.916 4700.4275)
      (12407.6489 4699.8473) (12409.7557 4698.7786) (12409.0229 4696.5344) (12406.0916 4692.7786) (12402.229 4687.7099)
      (12398.9466 4682.0763) (12397.4809 4676.9924) (12398.5038 4673.5725) (12401.9237 4672.5496) (12407.0076 4674.0153)
      (12412.6412 4677.2977) (12417.7099 4681.145) (12421.4656 4684.0763) (12423.7099 4684.8092) (12424.7786 4682.7176)
      (12425.374 4677.9847) (12426.229 4671.6641) (12427.8931 4665.3588) (12430.4427 4660.7328) (12433.5878 4659.0382)
      (12436.7328 4660.7328) (12439.2824 4665.3588) (12440.9466 4671.6641) (12441.8015 4677.9847) (12442.3969 4682.7176)
      (12443.4656 4684.8092) (12445.7099 4684.0763) (12449.4656 4681.145) (12454.5344 4677.2977) (12460.1679 4674.0153)
      (12465.2519 4672.5496) (12468.6718 4673.5725) (12469.6947 4676.9924) (12468.229 4682.0763) (12464.9466 4687.7099)
      (12461.084 4692.7786) (12458.1527 4696.5344) (12457.4198 4698.7786) (12459.5267 4699.8473) (12464.2595 4700.4275)
      (12470.5802 4701.2977) (12476.8855 4702.9618) (12481.5115 4705.5115) (12483.2061 4708.6565) (12481.5115 4711.8015)
      (12476.8855 4714.3511) (12470.5802 4716.0153) (12464.2595 4716.8702) (12459.5267 4717.4656) (12457.4198 4718.5344)
      (12458.1527 4720.7786) (12461.084 4724.5344) (12464.9466 4729.6031) (12468.229 4735.2366) (12469.6947 4740.3206)
      (12468.6718 4743.7405) (12465.2519 4744.7634) (12460.1679 4743.2977) (12454.5344 4740.0153) (12449.4656 4736.1527)
      (12445.7099 4733.2214) (12443.4656 4732.4885) (12442.3969 4734.5954) (12441.8015 4739.3282) (12440.9466 4745.6336)
      (12439.2824 4751.9389) (12436.7328 4756.5802) (12433.5878 4758.2748) (12430.4427 4756.5802) (12427.8931 4751.9389)
      (12426.229 4745.6336) (12425.374 4739.3282) (12424.7786 4734.5954) (12423.7099 4732.4885) (12421.4656 4733.2214)
      (12417.7099 4736.1527) (12412.6412 4740.0153) (12407.0076 4743.2977) (12401.9237 4744.7634) (12398.5038 4743.7405)
      (12397.4809 4740.3206) (12398.9466 4735.2366) (12402.229 4729.6031) (12406.0916 4724.5344) (12409.0229 4720.7786)
      (12409.7557 4718.5344) (12407.6489 4717.4656) (12402.916 4716.8702) (12396.5954 4716.0153) (12390.2901 4714.3511)
      (12385.6641 4711.8015)
    ))
    ; P3048 -- see feature_dimensions_mm.csv
    ("06_ORNAMENT" 1 (
      (12383.9695 4085.7557) (12385.6641 4082.6107) (12390.2901 4080.0611) (12396.5954 4078.3969) (12402.916 4077.5267)
      (12407.6489 4076.9466) (12409.7557 4075.8779) (12409.0229 4073.6336) (12406.0916 4069.8779) (12402.229 4064.8092)
      (12398.9466 4059.1756) (12397.4809 4054.0916) (12398.5038 4050.6718) (12401.9237 4049.6489) (12407.0076 4051.1145)
      (12412.6412 4054.3969) (12417.7099 4058.2595) (12421.4656 4061.1756) (12423.7099 4061.9084) (12424.7786 4059.8168)
      (12425.374 4055.084) (12426.229 4048.7634) (12427.8931 4042.458) (12430.4427 4037.8321) (12433.5878 4036.1374)
      (12436.7328 4037.8321) (12439.2824 4042.458) (12440.9466 4048.7634) (12441.8015 4055.084) (12442.3969 4059.8168)
      (12443.4656 4061.9084) (12445.7099 4061.1756) (12449.4656 4058.2595) (12454.5344 4054.3969) (12460.1679 4051.1145)
      (12465.2519 4049.6489) (12468.6718 4050.6718) (12469.6947 4054.0916) (12468.229 4059.1756) (12464.9466 4064.8092)
      (12461.084 4069.8779) (12458.1527 4073.6336) (12457.4198 4075.8779) (12459.5267 4076.9466) (12464.2595 4077.5267)
      (12470.5802 4078.3969) (12476.8855 4080.0611) (12481.5115 4082.6107) (12483.2061 4085.7557) (12481.5115 4088.9008)
      (12476.8855 4091.4504) (12470.5802 4093.1145) (12464.2595 4093.9695) (12459.5267 4094.5649) (12457.4198 4095.6336)
      (12458.1527 4097.8779) (12461.084 4101.6336) (12464.9466 4106.7023) (12468.229 4112.3359) (12469.6947 4117.4198)
      (12468.6718 4120.8397) (12465.2519 4121.8626) (12460.1679 4120.3969) (12454.5344 4117.1145) (12449.4656 4113.2519)
      (12445.7099 4110.3206) (12443.4656 4109.5878) (12442.3969 4111.6947) (12441.8015 4116.4275) (12440.9466 4122.7328)
      (12439.2824 4129.0382) (12436.7328 4133.6794) (12433.5878 4135.374) (12430.4427 4133.6794) (12427.8931 4129.0382)
      (12426.229 4122.7328) (12425.374 4116.4275) (12424.7786 4111.6947) (12423.7099 4109.5878) (12421.4656 4110.3206)
      (12417.7099 4113.2519) (12412.6412 4117.1145) (12407.0076 4120.3969) (12401.9237 4121.8626) (12398.5038 4120.8397)
      (12397.4809 4117.4198) (12398.9466 4112.3359) (12402.229 4106.7023) (12406.0916 4101.6336) (12409.0229 4097.8779)
      (12409.7557 4095.6336) (12407.6489 4094.5649) (12402.916 4093.9695) (12396.5954 4093.1145) (12390.2901 4091.4504)
      (12385.6641 4088.9008)
    ))
    ; P3049 -- see feature_dimensions_mm.csv
    ("06_ORNAMENT" 1 (
      (12415.2672 5409.4198) (12433.5878 5388.8092) (12451.9084 5409.4198) (12433.5878 5430.0305)
    ))
    ; P3050 -- see feature_dimensions_mm.csv
    ("06_ORNAMENT" 1 (
      (12415.2672 5097.9695) (12433.5878 5077.3588) (12451.9084 5097.9695) (12433.5878 5118.5802)
    ))
    ; P3051 -- see feature_dimensions_mm.csv
    ("06_ORNAMENT" 1 (
      (12415.2672 4786.5191) (12433.5878 4765.9084) (12451.9084 4786.5191) (12433.5878 4807.1298)
    ))
    ; P3052 -- see feature_dimensions_mm.csv
    ("06_ORNAMENT" 1 (
      (12415.2672 4163.6183) (12433.5878 4143.0076) (12451.9084 4163.6183) (12433.5878 4184.229)
    ))
    ; P3053 -- see feature_dimensions_mm.csv
    ("06_ORNAMENT" 1 (
      (12415.2672 3852.1679) (12433.145 3832.0611) (12434.0305 3832.0611) (12451.9084 3852.1679) (12433.5878 3872.7786)
    ))
    ; P3054 -- see feature_dimensions_mm.csv
    ("06_ORNAMENT" 1 (
      (12421.6794 5331.5573) (12422.5802 5326.9924) (12425.1603 5323.1298) (12429.0382 5320.5496) (12433.5878 5319.6489)
      (12438.1374 5320.5496) (12442.0153 5323.1298) (12444.5954 5326.9924) (12445.4962 5331.5573) (12444.5954 5336.1069)
      (12442.0153 5339.9695) (12438.1374 5342.5496) (12433.5878 5343.4656) (12429.0382 5342.5496) (12425.1603 5339.9695)
      (12422.5802 5336.1069)
    ))
    ; P3055 -- see feature_dimensions_mm.csv
    ("06_ORNAMENT" 1 (
      (12421.6794 5020.1069) (12422.5802 5015.542) (12425.1603 5011.6794) (12429.0382 5009.0992) (12433.5878 5008.1985)
      (12438.1374 5009.0992) (12442.0153 5011.6794) (12444.5954 5015.542) (12445.4962 5020.1069) (12444.5954 5024.6565)
      (12442.0153 5028.5191) (12438.1374 5031.0992) (12433.5878 5032.0153) (12429.0382 5031.0992) (12425.1603 5028.5191)
      (12422.5802 5024.6565)
    ))
    ; P3056 -- see feature_dimensions_mm.csv
    ("06_ORNAMENT" 1 (
      (12421.6794 4708.6565) (12422.5802 4704.0916) (12425.1603 4700.229) (12429.0382 4697.6489) (12433.5878 4696.7481)
      (12438.1374 4697.6489) (12442.0153 4700.229) (12444.5954 4704.0916) (12445.4962 4708.6565) (12444.5954 4713.2061)
      (12442.0153 4717.0687) (12438.1374 4719.6489) (12433.5878 4720.5649) (12429.0382 4719.6489) (12425.1603 4717.0687)
      (12422.5802 4713.2061)
    ))
    ; P3057 -- see feature_dimensions_mm.csv
    ("06_ORNAMENT" 1 (
      (12421.6794 4397.2061) (12422.5802 4392.6412) (12425.1603 4388.7786) (12429.0382 4386.1985) (12433.5878 4385.2977)
      (12438.1374 4386.1985) (12442.0153 4388.7786) (12444.5954 4392.6412) (12445.4962 4397.2061) (12444.5954 4401.7557)
      (12442.0153 4405.6183) (12438.1374 4408.1985) (12433.5878 4409.1145) (12429.0382 4408.1985) (12425.1603 4405.6183)
      (12422.5802 4401.7557)
    ))
    ; P3058 -- see feature_dimensions_mm.csv
    ("06_ORNAMENT" 1 (
      (12421.6794 4085.7557) (12422.5802 4081.1908) (12425.1603 4077.3282) (12429.0382 4074.7481) (12433.5878 4073.8473)
      (12438.1374 4074.7481) (12442.0153 4077.3282) (12444.5954 4081.1908) (12445.4962 4085.7557) (12444.5954 4090.3053)
      (12442.0153 4094.1679) (12438.1374 4096.7481) (12433.5878 4097.6641) (12429.0382 4096.7481) (12425.1603 4094.1679)
      (12422.5802 4090.3053)
    ))
    ; P3059 -- see feature_dimensions_mm.csv
    ("06_ORNAMENT" 1 (
      (12442.7481 3007.6336) (12473.2824 2977.0992) (12503.8168 3007.6336) (12473.2824 3038.1679)
    ))
    ; P3060 -- see feature_dimensions_mm.csv
    ("06_ORNAMENT" 1 (
      (12442.7481 2916.0305) (12473.2824 2885.4962) (12503.8168 2916.0305) (12473.2824 2946.5649)
    ))
    ; P3061 -- see feature_dimensions_mm.csv
    ("06_ORNAMENT" 1 (
      (12461.8321 5175.8321) (12463.5267 5172.687) (12468.1527 5170.1374) (12474.458 5168.4733) (12480.7786 5167.6031)
      (12485.5115 5167.0229) (12487.6183 5165.9542) (12486.8855 5163.7099) (12483.9542 5159.9542) (12480.0916 5154.8855)
      (12476.8092 5149.2519) (12475.3435 5144.1679) (12476.3664 5140.7481) (12479.7863 5139.7252) (12484.8702 5141.1908)
      (12490.5038 5144.4733) (12495.5725 5148.3206) (12499.3282 5151.2519) (12501.5725 5151.9847) (12502.6412 5149.8931)
      (12503.2366 5145.1603) (12504.0916 5138.8397) (12505.7557 5132.5344) (12508.3053 5127.9084) (12511.4504 5126.2137)
      (12514.5954 5127.9084) (12517.145 5132.5344) (12518.8092 5138.8397) (12519.6641 5145.1603) (12520.2595 5149.8931)
      (12521.3282 5151.9847) (12523.5725 5151.2519) (12527.3282 5148.3206) (12532.3969 5144.4733) (12538.0305 5141.1908)
      (12543.1145 5139.7252) (12546.5344 5140.7481) (12547.5573 5144.1679) (12546.0916 5149.2519) (12542.8092 5154.8855)
      (12538.9466 5159.9542) (12536.0153 5163.7099) (12535.2824 5165.9542) (12537.3893 5167.0229) (12542.1221 5167.6031)
      (12548.4427 5168.4733) (12554.7481 5170.1374) (12559.374 5172.687) (12561.0687 5175.8321) (12559.374 5178.9771)
      (12554.7481 5181.5267) (12548.4427 5183.1908) (12542.1221 5184.0458) (12537.3893 5184.6412) (12535.2824 5185.7099)
      (12536.0153 5187.9542) (12538.9466 5191.7099) (12542.8092 5196.7786) (12546.0916 5202.4122) (12547.5573 5207.4962)
      (12546.5344 5210.916) (12543.1145 5211.9389) (12538.0305 5210.4733) (12532.3969 5207.1908) (12527.3282 5203.3282)
      (12523.5725 5200.3969) (12521.3282 5199.6641) (12520.2595 5201.771) (12519.6641 5206.5038) (12518.8092 5212.8092)
      (12517.145 5219.1145) (12514.5954 5223.7557) (12511.4504 5225.4504) (12508.3053 5223.7557) (12505.7557 5219.1145)
      (12504.0916 5212.8092) (12503.2366 5206.5038) (12502.6412 5201.771) (12501.5725 5199.6641) (12499.3282 5200.3969)
      (12495.5725 5203.3282) (12490.5038 5207.1908) (12484.8702 5210.4733) (12479.7863 5211.9389) (12476.3664 5210.916)
      (12475.3435 5207.4962) (12476.8092 5202.4122) (12480.0916 5196.7786) (12483.9542 5191.7099) (12486.8855 5187.9542)
      (12487.6183 5185.7099) (12485.5115 5184.6412) (12480.7786 5184.0458) (12474.458 5183.1908) (12468.1527 5181.5267)
      (12463.5267 5178.9771)
    ))
    ; P3062 -- see feature_dimensions_mm.csv
    ("06_ORNAMENT" 1 (
      (12461.8321 4864.3817) (12463.5267 4861.2366) (12468.1527 4858.687) (12474.458 4857.0229) (12480.7786 4856.1527)
      (12485.5115 4855.5725) (12487.6183 4854.5038) (12486.8855 4852.2595) (12483.9542 4848.5038) (12480.0916 4843.4351)
      (12476.8092 4837.8015) (12475.3435 4832.7176) (12476.3664 4829.2977) (12479.7863 4828.2748) (12484.8702 4829.7405)
      (12490.5038 4833.0229) (12495.5725 4836.8702) (12499.3282 4839.8015) (12501.5725 4840.5344) (12502.6412 4838.4427)
      (12503.2366 4833.7099) (12504.0916 4827.3893) (12505.7557 4821.084) (12508.3053 4816.458) (12511.4504 4814.7634)
      (12514.5954 4816.458) (12517.145 4821.084) (12518.8092 4827.3893) (12519.6641 4833.7099) (12520.2595 4838.4427)
      (12521.3282 4840.5344) (12523.5725 4839.8015) (12527.3282 4836.8702) (12532.3969 4833.0229) (12538.0305 4829.7405)
      (12543.1145 4828.2748) (12546.5344 4829.2977) (12547.5573 4832.7176) (12546.0916 4837.8015) (12542.8092 4843.4351)
      (12538.9466 4848.5038) (12536.0153 4852.2595) (12535.2824 4854.5038) (12537.3893 4855.5725) (12542.1221 4856.1527)
      (12548.4427 4857.0229) (12554.7481 4858.687) (12559.374 4861.2366) (12561.0687 4864.3817) (12559.374 4867.5267)
      (12554.7481 4870.0763) (12548.4427 4871.7405) (12542.1221 4872.5954) (12537.3893 4873.1908) (12535.2824 4874.2595)
      (12536.0153 4876.5038) (12538.9466 4880.2595) (12542.8092 4885.3282) (12546.0916 4890.9618) (12547.5573 4896.0458)
      (12546.5344 4899.4656) (12543.1145 4900.4885) (12538.0305 4899.0229) (12532.3969 4895.7405) (12527.3282 4891.8779)
      (12523.5725 4888.9466) (12521.3282 4888.2137) (12520.2595 4890.3206) (12519.6641 4895.0534) (12518.8092 4901.3588)
      (12517.145 4907.6641) (12514.5954 4912.3053) (12511.4504 4914.0) (12508.3053 4912.3053) (12505.7557 4907.6641)
      (12504.0916 4901.3588) (12503.2366 4895.0534) (12502.6412 4890.3206) (12501.5725 4888.2137) (12499.3282 4888.9466)
      (12495.5725 4891.8779) (12490.5038 4895.7405) (12484.8702 4899.0229) (12479.7863 4900.4885) (12476.3664 4899.4656)
      (12475.3435 4896.0458) (12476.8092 4890.9618) (12480.0916 4885.3282) (12483.9542 4880.2595) (12486.8855 4876.5038)
      (12487.6183 4874.2595) (12485.5115 4873.1908) (12480.7786 4872.5954) (12474.458 4871.7405) (12468.1527 4870.0763)
      (12463.5267 4867.5267)
    ))
    ; P3063 -- see feature_dimensions_mm.csv
    ("06_ORNAMENT" 1 (
      (12461.8321 4552.9313) (12463.5267 4549.7863) (12468.1527 4547.2366) (12474.458 4545.5725) (12480.7786 4544.7023)
      (12485.5115 4544.1221) (12487.6183 4543.0534) (12486.8855 4540.8092) (12483.9542 4537.0534) (12480.0916 4531.9847)
      (12476.8092 4526.3511) (12475.3435 4521.2672) (12476.3664 4517.8473) (12479.7863 4516.8244) (12484.8702 4518.2901)
      (12490.5038 4521.5725) (12495.5725 4525.4198) (12499.3282 4528.3511) (12501.5725 4529.084) (12502.6412 4526.9924)
      (12503.2366 4522.2595) (12504.0916 4515.9389) (12505.7557 4509.6336) (12508.3053 4505.0076) (12511.4504 4503.313)
      (12514.5954 4505.0076) (12517.145 4509.6336) (12518.8092 4515.9389) (12519.6641 4522.2595) (12520.2595 4526.9924)
      (12521.3282 4529.084) (12523.5725 4528.3511) (12527.3282 4525.4198) (12532.3969 4521.5725) (12538.0305 4518.2901)
      (12543.1145 4516.8244) (12546.5344 4517.8473) (12547.5573 4521.2672) (12546.0916 4526.3511) (12542.8092 4531.9847)
      (12538.9466 4537.0534) (12536.0153 4540.8092) (12535.2824 4543.0534) (12537.3893 4544.1221) (12542.1221 4544.7023)
      (12548.4427 4545.5725) (12554.7481 4547.2366) (12559.374 4549.7863) (12561.0687 4552.9313) (12559.374 4556.0763)
      (12554.7481 4558.626) (12548.4427 4560.2901) (12542.1221 4561.145) (12537.3893 4561.7405) (12535.2824 4562.8092)
      (12536.0153 4565.0534) (12538.9466 4568.8092) (12542.8092 4573.8779) (12546.0916 4579.5115) (12547.5573 4584.5954)
      (12546.5344 4588.0153) (12543.1145 4589.0382) (12538.0305 4587.5725) (12532.3969 4584.2901) (12527.3282 4580.4275)
      (12523.5725 4577.4962) (12521.3282 4576.7634) (12520.2595 4578.8702) (12519.6641 4583.6031) (12518.8092 4589.9084)
      (12517.145 4596.2137) (12514.5954 4600.855) (12511.4504 4602.5496) (12508.3053 4600.855) (12505.7557 4596.2137)
      (12504.0916 4589.9084) (12503.2366 4583.6031) (12502.6412 4578.8702) (12501.5725 4576.7634) (12499.3282 4577.4962)
      (12495.5725 4580.4275) (12490.5038 4584.2901) (12484.8702 4587.5725) (12479.7863 4589.0382) (12476.3664 4588.0153)
      (12475.3435 4584.5954) (12476.8092 4579.5115) (12480.0916 4573.8779) (12483.9542 4568.8092) (12486.8855 4565.0534)
      (12487.6183 4562.8092) (12485.5115 4561.7405) (12480.7786 4561.145) (12474.458 4560.2901) (12468.1527 4558.626)
      (12463.5267 4556.0763)
    ))
    ; P3064 -- see feature_dimensions_mm.csv
    ("06_ORNAMENT" 1 (
      (12461.8321 4241.4809) (12463.5267 4238.3359) (12468.1527 4235.7863) (12474.458 4234.1221) (12480.7786 4233.2519)
      (12485.5115 4232.6718) (12487.6183 4231.6031) (12486.8855 4229.3588) (12483.9542 4225.6031) (12480.0916 4220.5344)
      (12476.8092 4214.9008) (12475.3435 4209.8168) (12476.3664 4206.3969) (12479.7863 4205.374) (12484.8702 4206.8397)
      (12490.5038 4210.1221) (12495.5725 4213.9695) (12499.3282 4216.9008) (12501.5725 4217.6336) (12502.6412 4215.542)
      (12503.2366 4210.8092) (12504.0916 4204.4885) (12505.7557 4198.1832) (12508.3053 4193.5573) (12511.4504 4191.8626)
      (12514.5954 4193.5573) (12517.145 4198.1832) (12518.8092 4204.4885) (12519.6641 4210.8092) (12520.2595 4215.542)
      (12521.3282 4217.6336) (12523.5725 4216.9008) (12527.3282 4213.9695) (12532.3969 4210.1221) (12538.0305 4206.8397)
      (12543.1145 4205.374) (12546.5344 4206.3969) (12547.5573 4209.8168) (12546.0916 4214.9008) (12542.8092 4220.5344)
      (12538.9466 4225.6031) (12536.0153 4229.3588) (12535.2824 4231.6031) (12537.3893 4232.6718) (12542.1221 4233.2519)
      (12548.4427 4234.1221) (12554.7481 4235.7863) (12559.374 4238.3359) (12561.0687 4241.4809) (12559.374 4244.626)
      (12554.7481 4247.1756) (12548.4427 4248.8397) (12542.1221 4249.6947) (12537.3893 4250.2901) (12535.2824 4251.3588)
      (12536.0153 4253.6031) (12538.9466 4257.3588) (12542.8092 4262.4275) (12546.0916 4268.0611) (12547.5573 4273.145)
      (12546.5344 4276.5649) (12543.1145 4277.5878) (12538.0305 4276.1221) (12532.3969 4272.8397) (12527.3282 4268.9771)
      (12523.5725 4266.0458) (12521.3282 4265.313) (12520.2595 4267.4198) (12519.6641 4272.1527) (12518.8092 4278.458)
      (12517.145 4284.7634) (12514.5954 4289.4046) (12511.4504 4291.0992) (12508.3053 4289.4046) (12505.7557 4284.7634)
      (12504.0916 4278.458) (12503.2366 4272.1527) (12502.6412 4267.4198) (12501.5725 4265.313) (12499.3282 4266.0458)
      (12495.5725 4268.9771) (12490.5038 4272.8397) (12484.8702 4276.1221) (12479.7863 4277.5878) (12476.3664 4276.5649)
      (12475.3435 4273.145) (12476.8092 4268.0611) (12480.0916 4262.4275) (12483.9542 4257.3588) (12486.8855 4253.6031)
      (12487.6183 4251.3588) (12485.5115 4250.2901) (12480.7786 4249.6947) (12474.458 4248.8397) (12468.1527 4247.1756)
      (12463.5267 4244.626)
    ))
    ; P3065 -- see feature_dimensions_mm.csv
    ("06_ORNAMENT" 1 (
      (12461.8321 3930.0305) (12463.5267 3926.8855) (12468.1527 3924.3359) (12474.458 3922.6718) (12480.7786 3921.8015)
      (12485.5115 3921.2214) (12487.6183 3920.1527) (12486.8855 3917.9084) (12483.9542 3914.1527) (12480.0916 3909.084)
      (12476.8092 3903.4504) (12475.3435 3898.3664) (12476.3664 3894.9466) (12479.7863 3893.9237) (12484.8702 3895.3893)
      (12490.5038 3898.6718) (12495.5725 3902.5191) (12499.3282 3905.4504) (12501.5725 3906.1832) (12502.6412 3904.0916)
      (12503.2366 3899.3588) (12504.0916 3893.0382) (12505.7557 3886.7328) (12508.3053 3882.1069) (12511.4504 3880.4122)
      (12514.5954 3882.1069) (12517.145 3886.7328) (12518.8092 3893.0382) (12519.6641 3899.3588) (12520.2595 3904.0916)
      (12521.3282 3906.1832) (12523.5725 3905.4504) (12527.3282 3902.5191) (12532.3969 3898.6718) (12538.0305 3895.3893)
      (12543.1145 3893.9237) (12546.5344 3894.9466) (12547.5573 3898.3664) (12546.0916 3903.4504) (12542.8092 3909.084)
      (12538.9466 3914.1527) (12536.0153 3917.9084) (12535.2824 3920.1527) (12537.3893 3921.2214) (12542.1221 3921.8015)
      (12548.4427 3922.6718) (12554.7481 3924.3359) (12559.374 3926.8855) (12561.0687 3930.0305) (12559.374 3933.1756)
      (12554.7481 3935.7252) (12548.4427 3937.3893) (12542.1221 3938.2443) (12537.3893 3938.8397) (12535.2824 3939.9084)
      (12536.0153 3942.1527) (12538.9466 3945.9084) (12542.8092 3950.9771) (12546.0916 3956.6107) (12547.5573 3961.6947)
      (12546.5344 3965.1145) (12543.1145 3966.1374) (12538.0305 3964.6718) (12532.3969 3961.3893) (12527.3282 3957.5267)
      (12523.5725 3954.5954) (12521.3282 3953.8626) (12520.2595 3955.9695) (12519.6641 3960.7023) (12518.8092 3967.0076)
      (12517.145 3973.313) (12514.5954 3977.9542) (12511.4504 3979.6489) (12508.3053 3977.9542) (12505.7557 3973.313)
      (12504.0916 3967.0076) (12503.2366 3960.7023) (12502.6412 3955.9695) (12501.5725 3953.8626) (12499.3282 3954.5954)
      (12495.5725 3957.5267) (12490.5038 3961.3893) (12484.8702 3964.6718) (12479.7863 3966.1374) (12476.3664 3965.1145)
      (12475.3435 3961.6947) (12476.8092 3956.6107) (12480.0916 3950.9771) (12483.9542 3945.9084) (12486.8855 3942.1527)
      (12487.6183 3939.9084) (12485.5115 3938.8397) (12480.7786 3938.2443) (12474.458 3937.3893) (12468.1527 3935.7252)
      (12463.5267 3933.1756)
    ))
    ; P3066 -- see feature_dimensions_mm.csv
    ("06_ORNAMENT" 1 (
      (12493.1298 5253.6947) (12511.4504 5233.084) (12529.771 5253.6947) (12511.4504 5274.3053)
    ))
    ; P3067 -- see feature_dimensions_mm.csv
    ("06_ORNAMENT" 1 (
      (12493.1298 4942.2443) (12511.4504 4921.6336) (12529.771 4942.2443) (12511.4504 4962.855)
    ))
    ; P3068 -- see feature_dimensions_mm.csv
    ("06_ORNAMENT" 1 (
      (12493.1298 4630.7939) (12511.4504 4610.1832) (12529.771 4630.7939) (12511.4504 4651.4046)
    ))
    ; P3069 -- see feature_dimensions_mm.csv
    ("06_ORNAMENT" 1 (
      (12493.1298 4319.3435) (12511.4504 4298.7328) (12529.771 4319.3435) (12511.4504 4339.9542)
    ))
    ; P3070 -- see feature_dimensions_mm.csv
    ("06_ORNAMENT" 1 (
      (12493.1298 4007.8931) (12511.4504 3987.2824) (12529.771 4007.8931) (12511.4504 4028.5038)
    ))
    ; P3071 -- see feature_dimensions_mm.csv
    ("06_ORNAMENT" 1 (
      (12499.542 5175.8321) (12500.4427 5171.2672) (12503.0229 5167.4046) (12506.9008 5164.8244) (12511.4504 5163.9237)
      (12516.0 5164.8244) (12519.8779 5167.4046) (12522.458 5171.2672) (12523.3588 5175.8321) (12522.458 5180.3817)
      (12519.8779 5184.2443) (12516.0 5186.8244) (12511.4504 5187.7405) (12506.9008 5186.8244) (12503.0229 5184.2443)
      (12500.4427 5180.3817)
    ))
    ; P3072 -- see feature_dimensions_mm.csv
    ("06_ORNAMENT" 1 (
      (12499.542 4864.3817) (12500.4427 4859.8168) (12503.0229 4855.9542) (12506.9008 4853.374) (12511.4504 4852.4733)
      (12516.0 4853.374) (12519.8779 4855.9542) (12522.458 4859.8168) (12523.3588 4864.3817) (12522.458 4868.9313)
      (12519.8779 4872.7939) (12516.0 4875.374) (12511.4504 4876.2901) (12506.9008 4875.374) (12503.0229 4872.7939)
      (12500.4427 4868.9313)
    ))
    ; P3073 -- see feature_dimensions_mm.csv
    ("06_ORNAMENT" 1 (
      (12499.542 4552.9313) (12500.4427 4548.3664) (12503.0229 4544.5038) (12506.9008 4541.9237) (12511.4504 4541.0229)
      (12516.0 4541.9237) (12519.8779 4544.5038) (12522.458 4548.3664) (12523.3588 4552.9313) (12522.458 4557.4809)
      (12519.8779 4561.3435) (12516.0 4563.9237) (12511.4504 4564.8397) (12506.9008 4563.9237) (12503.0229 4561.3435)
      (12500.4427 4557.4809)
    ))
    ; P3074 -- see feature_dimensions_mm.csv
    ("06_ORNAMENT" 1 (
      (12499.542 4241.4809) (12500.4427 4236.916) (12503.0229 4233.0534) (12506.9008 4230.4733) (12511.4504 4229.5725)
      (12516.0 4230.4733) (12519.8779 4233.0534) (12522.458 4236.916) (12523.3588 4241.4809) (12522.458 4246.0305)
      (12519.8779 4249.8931) (12516.0 4252.4733) (12511.4504 4253.3893) (12506.9008 4252.4733) (12503.0229 4249.8931)
      (12500.4427 4246.0305)
    ))
    ; P3075 -- see feature_dimensions_mm.csv
    ("06_ORNAMENT" 1 (
      (12499.542 3930.0305) (12500.4427 3925.4656) (12503.0229 3921.6031) (12506.9008 3919.0229) (12511.4504 3918.1221)
      (12516.0 3919.0229) (12519.8779 3921.6031) (12522.458 3925.4656) (12523.3588 3930.0305) (12522.458 3934.5802)
      (12519.8779 3938.4427) (12516.0 3941.0229) (12511.4504 3941.9389) (12506.9008 3941.0229) (12503.0229 3938.4427)
      (12500.4427 3934.5802)
    ))
    ; P3076 -- see feature_dimensions_mm.csv
    ("06_ORNAMENT" 1 (
      (12503.8168 7374.0458) (12564.8855 7343.5115) (12625.9542 7374.0458) (12564.8855 7404.5802)
    ))
    ; P3077 -- see feature_dimensions_mm.csv
    ("06_ORNAMENT" 1 (
      (12503.8168 7282.4427) (12564.8855 7251.9084) (12625.9542 7282.4427) (12564.8855 7312.9771)
    ))
    ; P3078 -- see feature_dimensions_mm.csv
    ("06_ORNAMENT" 1 (
      (12503.8168 7190.8397) (12564.8855 7160.3053) (12625.9542 7190.8397) (12564.8855 7221.374)
    ))
    ; P3079 -- see feature_dimensions_mm.csv
    ("06_ORNAMENT" 1 (
      (12510.3206 1425.9237) (12511.4504 1409.9084) (12526.6412 1418.2443) (12541.8779 1428.458) (12556.9313 1440.3511)
      (12571.542 1453.771) (12585.4809 1468.5496) (12598.5191 1484.5191) (12610.4122 1501.4962) (12620.9008 1519.3435)
      (12629.771 1537.8473) (12636.7634 1556.8702) (12641.6336 1576.2443) (12644.1679 1595.771) (12644.1069 1615.313)
      (12641.2214 1634.687) (12622.4733 1626.5802) (12605.0229 1616.0153) (12588.9466 1603.313) (12574.2595 1588.7634)
      (12560.9771 1572.7023) (12549.1756 1555.4046) (12538.855 1537.1908) (12530.0763 1518.3817) (12522.855 1499.2519)
      (12517.2366 1480.1527) (12513.2366 1461.3435) (12510.9313 1443.1756)
    ))
    ; P3080 -- see feature_dimensions_mm.csv
    ("06_ORNAMENT" 1 (
      (12511.0687 2053.6794) (12512.2901 2035.3893) (12515.0687 2016.3969) (12519.3893 1997.0382) (12525.2061 1977.5725)
      (12532.5191 1958.2901) (12541.2977 1939.5115) (12551.4962 1921.4962) (12563.084 1904.5649) (12576.0763 1889.0076)
      (12590.3969 1875.084) (12606.0458 1863.1298) (12623.0076 1853.4198) (12641.2214 1846.229) (12643.5725 1866.5344)
      (12643.145 1886.916) (12640.1832 1907.1908) (12634.9466 1927.1908) (12627.6641 1946.7176) (12618.5802 1965.5878)
      (12607.9695 1983.6336) (12596.0763 2000.6412) (12583.1298 2016.458) (12569.3893 2030.8855) (12555.0992 2043.7252)
      (12540.5191 2054.8244) (12525.8779 2063.9695) (12511.4504 2071.0076)
    ))
    ; P3081 -- see feature_dimensions_mm.csv
    ("06_ORNAMENT" 1 (
      (12539.6947 5331.5573) (12541.3893 5328.4122) (12546.0153 5325.8626) (12552.3206 5324.1985) (12558.6412 5323.3282)
      (12563.374 5322.7481) (12565.4809 5321.6794) (12564.7481 5319.4351) (12561.8168 5315.6794) (12557.9542 5310.6107)
      (12554.6718 5304.9771) (12553.2061 5299.8931) (12554.229 5296.4733) (12557.6489 5295.4504) (12562.7328 5296.916)
      (12568.3664 5300.1985) (12573.4351 5304.0458) (12577.1908 5306.9771) (12579.4351 5307.7099) (12580.5038 5305.6183)
      (12581.0992 5300.8855) (12581.9542 5294.5649) (12583.6183 5288.2595) (12586.1679 5283.6336) (12589.313 5281.9389)
      (12592.458 5283.6336) (12595.0076 5288.2595) (12596.6718 5294.5649) (12597.5267 5300.8855) (12598.1221 5305.6183)
      (12599.1908 5307.7099) (12601.4351 5306.9771) (12605.1908 5304.0458) (12610.2595 5300.1985) (12615.8931 5296.916)
      (12620.9771 5295.4504) (12624.3969 5296.4733) (12625.4198 5299.8931) (12623.9542 5304.9771) (12620.6718 5310.6107)
      (12616.8092 5315.6794) (12613.8779 5319.4351) (12613.145 5321.6794) (12615.2519 5322.7481) (12619.9847 5323.3282)
      (12626.3053 5324.1985) (12632.6107 5325.8626) (12637.2366 5328.4122) (12638.9313 5331.5573) (12637.2366 5334.7023)
      (12632.6107 5337.2519) (12626.3053 5338.916) (12619.9847 5339.771) (12615.2519 5340.3664) (12613.145 5341.4351)
      (12613.8779 5343.6794) (12616.8092 5347.4351) (12620.6718 5352.5038) (12623.9542 5358.1374) (12625.4198 5363.2214)
      (12624.3969 5366.6412) (12620.9771 5367.6641) (12615.8931 5366.1985) (12610.2595 5362.916) (12605.1908 5359.0534)
      (12601.4351 5356.1221) (12599.1908 5355.3893) (12598.1221 5357.4962) (12597.5267 5362.229) (12596.6718 5368.5344)
      (12595.0076 5374.8397) (12592.458 5379.4809) (12589.313 5381.1756) (12586.1679 5379.4809) (12583.6183 5374.8397)
      (12581.9542 5368.5344) (12581.0992 5362.229) (12580.5038 5357.4962) (12579.4351 5355.3893) (12577.1908 5356.1221)
      (12573.4351 5359.0534) (12568.3664 5362.916) (12562.7328 5366.1985) (12557.6489 5367.6641) (12554.229 5366.6412)
      (12553.2061 5363.2214) (12554.6718 5358.1374) (12557.9542 5352.5038) (12561.8168 5347.4351) (12564.7481 5343.6794)
      (12565.4809 5341.4351) (12563.374 5340.3664) (12558.6412 5339.771) (12552.3206 5338.916) (12546.0153 5337.2519)
      (12541.3893 5334.7023)
    ))
    ; P3082 -- see feature_dimensions_mm.csv
    ("06_ORNAMENT" 1 (
      (12539.6947 5020.1069) (12541.3893 5016.9618) (12546.0153 5014.4122) (12552.3206 5012.7481) (12558.6412 5011.8779)
      (12563.374 5011.2977) (12565.4809 5010.229) (12564.7481 5007.9847) (12561.8168 5004.229) (12557.9542 4999.1603)
      (12554.6718 4993.5267) (12553.2061 4988.4427) (12554.229 4985.0229) (12557.6489 4984.0) (12562.7328 4985.4656)
      (12568.3664 4988.7481) (12573.4351 4992.5954) (12577.1908 4995.5267) (12579.4351 4996.2595) (12580.5038 4994.1679)
      (12581.0992 4989.4351) (12581.9542 4983.1145) (12583.6183 4976.8092) (12586.1679 4972.1832) (12589.313 4970.4885)
      (12592.458 4972.1832) (12595.0076 4976.8092) (12596.6718 4983.1145) (12597.5267 4989.4351) (12598.1221 4994.1679)
      (12599.1908 4996.2595) (12601.4351 4995.5267) (12605.1908 4992.5954) (12610.2595 4988.7481) (12615.8931 4985.4656)
      (12620.9771 4984.0) (12624.3969 4985.0229) (12625.4198 4988.4427) (12623.9542 4993.5267) (12620.6718 4999.1603)
      (12616.8092 5004.229) (12613.8779 5007.9847) (12613.145 5010.229) (12615.2519 5011.2977) (12619.9847 5011.8779)
      (12626.3053 5012.7481) (12632.6107 5014.4122) (12637.2366 5016.9618) (12638.9313 5020.1069) (12637.2366 5023.2519)
      (12632.6107 5025.8015) (12626.3053 5027.4656) (12619.9847 5028.3206) (12615.2519 5028.916) (12613.145 5029.9847)
      (12613.8779 5032.229) (12616.8092 5035.9847) (12620.6718 5041.0534) (12623.9542 5046.687) (12625.4198 5051.771)
      (12624.3969 5055.1908) (12620.9771 5056.2137) (12615.8931 5054.7481) (12610.2595 5051.4656) (12605.1908 5047.6031)
      (12601.4351 5044.6718) (12599.1908 5043.9389) (12598.1221 5046.0458) (12597.5267 5050.7786) (12596.6718 5057.084)
      (12595.0076 5063.3893) (12592.458 5068.0305) (12589.313 5069.7252) (12586.1679 5068.0305) (12583.6183 5063.3893)
      (12581.9542 5057.084) (12581.0992 5050.7786) (12580.5038 5046.0458) (12579.4351 5043.9389) (12577.1908 5044.6718)
      (12573.4351 5047.6031) (12568.3664 5051.4656) (12562.7328 5054.7481) (12557.6489 5056.2137) (12554.229 5055.1908)
      (12553.2061 5051.771) (12554.6718 5046.687) (12557.9542 5041.0534) (12561.8168 5035.9847) (12564.7481 5032.229)
      (12565.4809 5029.9847) (12563.374 5028.916) (12558.6412 5028.3206) (12552.3206 5027.4656) (12546.0153 5025.8015)
      (12541.3893 5023.2519)
    ))
    ; P3083 -- see feature_dimensions_mm.csv
    ("06_ORNAMENT" 1 (
      (12539.6947 4708.6565) (12541.3893 4705.5115) (12546.0153 4702.9618) (12552.3206 4701.2977) (12558.6412 4700.4275)
      (12563.374 4699.8473) (12565.4809 4698.7786) (12564.7481 4696.5344) (12561.8168 4692.7786) (12557.9542 4687.7099)
      (12554.6718 4682.0763) (12553.2061 4676.9924) (12554.229 4673.5725) (12557.6489 4672.5496) (12562.7328 4674.0153)
      (12568.3664 4677.2977) (12573.4351 4681.145) (12577.1908 4684.0763) (12579.4351 4684.8092) (12580.5038 4682.7176)
      (12581.0992 4677.9847) (12581.9542 4671.6641) (12583.6183 4665.3588) (12586.1679 4660.7328) (12589.313 4659.0382)
      (12592.458 4660.7328) (12595.0076 4665.3588) (12596.6718 4671.6641) (12597.5267 4677.9847) (12598.1221 4682.7176)
      (12599.1908 4684.8092) (12601.4351 4684.0763) (12605.1908 4681.145) (12610.2595 4677.2977) (12615.8931 4674.0153)
      (12620.9771 4672.5496) (12624.3969 4673.5725) (12625.4198 4676.9924) (12623.9542 4682.0763) (12620.6718 4687.7099)
      (12616.8092 4692.7786) (12613.8779 4696.5344) (12613.145 4698.7786) (12615.2519 4699.8473) (12619.9847 4700.4275)
      (12626.3053 4701.2977) (12632.6107 4702.9618) (12637.2366 4705.5115) (12638.9313 4708.6565) (12637.2366 4711.8015)
      (12632.6107 4714.3511) (12626.3053 4716.0153) (12619.9847 4716.8702) (12615.2519 4717.4656) (12613.145 4718.5344)
      (12613.8779 4720.7786) (12616.8092 4724.5344) (12620.6718 4729.6031) (12623.9542 4735.2366) (12625.4198 4740.3206)
      (12624.3969 4743.7405) (12620.9771 4744.7634) (12615.8931 4743.2977) (12610.2595 4740.0153) (12605.1908 4736.1527)
      (12601.4351 4733.2214) (12599.1908 4732.4885) (12598.1221 4734.5954) (12597.5267 4739.3282) (12596.6718 4745.6336)
      (12595.0076 4751.9389) (12592.458 4756.5802) (12589.313 4758.2748) (12586.1679 4756.5802) (12583.6183 4751.9389)
      (12581.9542 4745.6336) (12581.0992 4739.3282) (12580.5038 4734.5954) (12579.4351 4732.4885) (12577.1908 4733.2214)
      (12573.4351 4736.1527) (12568.3664 4740.0153) (12562.7328 4743.2977) (12557.6489 4744.7634) (12554.229 4743.7405)
      (12553.2061 4740.3206) (12554.6718 4735.2366) (12557.9542 4729.6031) (12561.8168 4724.5344) (12564.7481 4720.7786)
      (12565.4809 4718.5344) (12563.374 4717.4656) (12558.6412 4716.8702) (12552.3206 4716.0153) (12546.0153 4714.3511)
      (12541.3893 4711.8015)
    ))
    ; P3084 -- see feature_dimensions_mm.csv
    ("06_ORNAMENT" 1 (
      (12539.6947 4085.7557) (12541.3893 4082.6107) (12546.0153 4080.0611) (12552.3206 4078.3969) (12558.6412 4077.5267)
      (12563.374 4076.9466) (12565.4809 4075.8779) (12564.7481 4073.6336) (12561.8168 4069.8779) (12557.9542 4064.8092)
      (12554.6718 4059.1756) (12553.2061 4054.0916) (12554.229 4050.6718) (12557.6489 4049.6489) (12562.7328 4051.1145)
      (12568.3664 4054.3969) (12573.4351 4058.2595) (12577.1908 4061.1756) (12579.4351 4061.9084) (12580.5038 4059.8168)
      (12581.0992 4055.084) (12581.9542 4048.7634) (12583.6183 4042.458) (12586.1679 4037.8321) (12589.313 4036.1374)
      (12592.458 4037.8321) (12595.0076 4042.458) (12596.6718 4048.7634) (12597.5267 4055.084) (12598.1221 4059.8168)
      (12599.1908 4061.9084) (12601.4351 4061.1756) (12605.1908 4058.2595) (12610.2595 4054.3969) (12615.8931 4051.1145)
      (12620.9771 4049.6489) (12624.3969 4050.6718) (12625.4198 4054.0916) (12623.9542 4059.1756) (12620.6718 4064.8092)
      (12616.8092 4069.8779) (12613.8779 4073.6336) (12613.145 4075.8779) (12615.2519 4076.9466) (12619.9847 4077.5267)
      (12626.3053 4078.3969) (12632.6107 4080.0611) (12637.2366 4082.6107) (12638.9313 4085.7557) (12637.2366 4088.9008)
      (12632.6107 4091.4504) (12626.3053 4093.1145) (12619.9847 4093.9695) (12615.2519 4094.5649) (12613.145 4095.6336)
      (12613.8779 4097.8779) (12616.8092 4101.6336) (12620.6718 4106.7023) (12623.9542 4112.3359) (12625.4198 4117.4198)
      (12624.3969 4120.8397) (12620.9771 4121.8626) (12615.8931 4120.3969) (12610.2595 4117.1145) (12605.1908 4113.2519)
      (12601.4351 4110.3206) (12599.1908 4109.5878) (12598.1221 4111.6947) (12597.5267 4116.4275) (12596.6718 4122.7328)
      (12595.0076 4129.0382) (12592.458 4133.6794) (12589.313 4135.374) (12586.1679 4133.6794) (12583.6183 4129.0382)
      (12581.9542 4122.7328) (12581.0992 4116.4275) (12580.5038 4111.6947) (12579.4351 4109.5878) (12577.1908 4110.3206)
      (12573.4351 4113.2519) (12568.3664 4117.1145) (12562.7328 4120.3969) (12557.6489 4121.8626) (12554.229 4120.8397)
      (12553.2061 4117.4198) (12554.6718 4112.3359) (12557.9542 4106.7023) (12561.8168 4101.6336) (12564.7481 4097.8779)
      (12565.4809 4095.6336) (12563.374 4094.5649) (12558.6412 4093.9695) (12552.3206 4093.1145) (12546.0153 4091.4504)
      (12541.3893 4088.9008)
    ))
    ; P3085 -- see feature_dimensions_mm.csv
    ("06_ORNAMENT" 1 (
      (12564.8855 6000.0) (12567.1298 5985.8473) (12573.6336 5973.084) (12583.771 5962.9466) (12596.5344 5956.4427)
      (12610.687 5954.1985) (12624.8397 5956.4427) (12637.6031 5962.9466) (12647.7405 5973.084) (12654.2443 5985.8473)
      (12656.4885 6000.0) (12654.2443 6014.1527) (12647.7405 6026.916) (12637.6031 6037.0534) (12624.8397 6043.5573)
      (12610.687 6045.8015) (12596.5344 6043.5573) (12583.771 6037.0534) (12573.6336 6026.916) (12567.1298 6014.1527)
    ))
    ; P3086 -- see feature_dimensions_mm.csv
    ("06_ORNAMENT" 1 (
      (12566.3511 1321.6947) (12566.3969 1309.8931) (12567.3893 1298.4885) (12569.3282 1287.6794) (12572.1527 1277.6489)
      (12575.8473 1268.5496) (12583.8168 1275.4351) (12591.4656 1283.4046) (12598.687 1292.3359) (12605.3588 1302.0763)
      (12611.3435 1312.5038) (12616.5496 1323.5115) (12620.8397 1334.9313) (12624.0916 1346.6565) (12626.1985 1358.5649)
      (12627.0534 1370.5038) (12626.5038 1382.3511) (12624.458 1393.9695) (12620.7786 1405.2366) (12615.3588 1416.0305)
      (12605.1145 1408.7786) (12596.1374 1400.3053) (12588.4275 1390.7786) (12581.9237 1380.3817) (12576.5954 1369.2824)
      (12572.4122 1357.6947) (12569.3282 1345.771) (12567.3282 1333.7099)
    ))
    ; P3087 -- see feature_dimensions_mm.csv
    ("06_ORNAMENT" 1 (
      (12567.0534 2168.5802) (12567.0687 2156.5496) (12568.0763 2144.4122) (12570.0763 2132.3817) (12573.1145 2120.5954)
      (12577.2366 2109.2366) (12582.4733 2098.4733) (12588.8702 2088.4885) (12596.458 2079.4504) (12605.2672 2071.5267)
      (12615.3588 2064.8855) (12620.6107 2076.2901) (12624.1374 2088.1069) (12626.0611 2100.229) (12626.4885 2112.4885)
      (12625.5573 2124.7481) (12623.3893 2136.8855) (12620.0916 2148.7481) (12615.8015 2160.1985) (12610.626 2171.084)
      (12604.7023 2181.2977) (12598.1374 2190.6565) (12591.0534 2199.0534) (12583.5878 2206.3359) (12575.8473 2212.3664)
      (12572.3817 2202.4122) (12569.7405 2191.6794) (12567.9542 2180.3511)
    ))
    ; P3088 -- see feature_dimensions_mm.csv
    ("06_ORNAMENT" 1 (
      (12570.9924 5409.4198) (12589.313 5388.8092) (12607.4962 5409.2519) (12604.5649 5410.9313) (12582.3359 5422.1679)
    ))
    ; P3089 -- see feature_dimensions_mm.csv
    ("06_ORNAMENT" 1 (
      (12570.9924 5097.9695) (12589.313 5077.3588) (12607.6336 5097.9695) (12589.313 5118.5802)
    ))
    ; P3090 -- see feature_dimensions_mm.csv
    ("06_ORNAMENT" 1 (
      (12570.9924 4786.5191) (12589.313 4765.9084) (12607.6336 4786.5191) (12589.313 4807.1298)
    ))
    ; P3091 -- see feature_dimensions_mm.csv
    ("06_ORNAMENT" 1 (
      (12570.9924 4163.6183) (12589.313 4143.0076) (12607.6336 4163.6183) (12589.313 4184.229)
    ))
    ; P3092 -- see feature_dimensions_mm.csv
    ("06_ORNAMENT" 1 (
      (12570.9924 3852.1679) (12588.8702 3832.0611) (12589.7557 3832.0611) (12607.6336 3852.1679) (12589.313 3872.7786)
    ))
    ; P3093 -- see feature_dimensions_mm.csv
    ("06_ORNAMENT" 1 (
      (12577.4046 5331.5573) (12578.3053 5326.9924) (12580.8855 5323.1298) (12584.7634 5320.5496) (12589.313 5319.6489)
      (12593.8626 5320.5496) (12597.7405 5323.1298) (12600.3206 5326.9924) (12601.2214 5331.5573) (12600.3206 5336.1069)
      (12597.7405 5339.9695) (12593.8626 5342.5496) (12589.313 5343.4656) (12584.7634 5342.5496) (12580.8855 5339.9695)
      (12578.3053 5336.1069)
    ))
    ; P3094 -- see feature_dimensions_mm.csv
    ("06_ORNAMENT" 1 (
      (12577.4046 5020.1069) (12578.3053 5015.542) (12580.8855 5011.6794) (12584.7634 5009.0992) (12589.313 5008.1985)
      (12593.8626 5009.0992) (12597.7405 5011.6794) (12600.3206 5015.542) (12601.2214 5020.1069) (12600.3206 5024.6565)
      (12597.7405 5028.5191) (12593.8626 5031.0992) (12589.313 5032.0153) (12584.7634 5031.0992) (12580.8855 5028.5191)
      (12578.3053 5024.6565)
    ))
    ; P3095 -- see feature_dimensions_mm.csv
    ("06_ORNAMENT" 1 (
      (12577.4046 4708.6565) (12578.3053 4704.0916) (12580.8855 4700.229) (12584.7634 4697.6489) (12589.313 4696.7481)
      (12593.8626 4697.6489) (12597.7405 4700.229) (12600.3206 4704.0916) (12601.2214 4708.6565) (12600.3206 4713.2061)
      (12597.7405 4717.0687) (12593.8626 4719.6489) (12589.313 4720.5649) (12584.7634 4719.6489) (12580.8855 4717.0687)
      (12578.3053 4713.2061)
    ))
    ; P3096 -- see feature_dimensions_mm.csv
    ("06_ORNAMENT" 1 (
      (12577.4046 4397.2061) (12578.3053 4392.6412) (12580.8855 4388.7786) (12584.7634 4386.1985) (12589.313 4385.2977)
      (12593.8626 4386.1985) (12597.7405 4388.7786) (12600.3206 4392.6412) (12601.2214 4397.2061) (12600.3206 4401.7557)
      (12597.7405 4405.6183) (12593.8626 4408.1985) (12589.313 4409.1145) (12584.7634 4408.1985) (12580.8855 4405.6183)
      (12578.3053 4401.7557)
    ))
    ; P3097 -- see feature_dimensions_mm.csv
    ("06_ORNAMENT" 1 (
      (12577.4046 4085.7557) (12578.3053 4081.1908) (12580.8855 4077.3282) (12584.7634 4074.7481) (12589.313 4073.8473)
      (12593.8626 4074.7481) (12597.7405 4077.3282) (12600.3206 4081.1908) (12601.2214 4085.7557) (12600.3206 4090.3053)
      (12597.7405 4094.1679) (12593.8626 4096.7481) (12589.313 4097.6641) (12584.7634 4096.7481) (12580.8855 4094.1679)
      (12578.3053 4090.3053)
    ))
    ; P3098 -- see feature_dimensions_mm.csv
    ("06_ORNAMENT" 1 (
      (12584.7939 5900.4885) (12592.7786 5909.9542) (12600.1069 5919.5878) (12605.8473 5926.1985) (12610.687 5928.5496)
      (12615.5267 5926.1985) (12621.2672 5919.5878) (12628.5954 5909.9542) (12633.9084 5903.6489) (12629.5878 5903.8015)
      (12607.2214 5903.0229) (12585.0229 5900.5191)
    ))
    ; P3099 -- see feature_dimensions_mm.csv
    ("06_ORNAMENT" 1 (
      (12595.4198 1740.458) (12597.4809 1719.6031) (12603.5573 1699.5573) (12613.4351 1681.084) (12626.7176 1664.8855)
      (12642.916 1651.6031) (12661.3893 1641.7252) (12681.4351 1635.6336) (12702.2901 1633.5878) (12723.145 1635.6336)
      (12743.1908 1641.7252) (12761.6641 1651.6031) (12777.8626 1664.8855) (12791.145 1681.084) (12801.0229 1699.5573)
      (12807.1145 1719.6031) (12809.1603 1740.458) (12807.1145 1761.313) (12801.0229 1781.3588) (12791.145 1799.8321)
      (12777.8626 1816.0305) (12761.6641 1829.313) (12743.1908 1839.1908) (12723.145 1845.2672) (12702.2901 1847.3282)
      (12681.4351 1845.2672) (12661.3893 1839.1908) (12642.916 1829.313) (12626.7176 1816.0305) (12613.4351 1799.8321)
      (12603.5573 1781.3588) (12597.4809 1761.313)
    ))
    ; P3100 -- see feature_dimensions_mm.csv
    ("06_ORNAMENT" 1 (
      (12617.5573 5175.8321) (12619.2519 5172.687) (12623.8779 5170.1374) (12630.1832 5168.4733) (12636.5038 5167.6031)
      (12641.2366 5167.0229) (12643.3435 5165.9542) (12642.6107 5163.7099) (12639.6794 5159.9542) (12635.8168 5154.8855)
      (12632.5344 5149.2519) (12631.0687 5144.1679) (12632.0916 5140.7481) (12635.5115 5139.7252) (12640.5954 5141.1908)
      (12646.229 5144.4733) (12651.2977 5148.3206) (12655.0534 5151.2519) (12657.2977 5151.9847) (12658.3664 5149.8931)
      (12658.9618 5145.1603) (12659.8168 5138.8397) (12661.4809 5132.5344) (12664.0305 5127.9084) (12667.1756 5126.2137)
      (12670.3206 5127.9084) (12672.8702 5132.5344) (12674.5344 5138.8397) (12675.3893 5145.1603) (12675.9847 5149.8931)
      (12677.0534 5151.9847) (12679.2977 5151.2519) (12683.0534 5148.3206) (12688.1221 5144.4733) (12693.7557 5141.1908)
      (12698.8397 5139.7252) (12702.2595 5140.7481) (12703.2824 5144.1679) (12701.8168 5149.2519) (12698.5344 5154.8855)
      (12694.6718 5159.9542) (12691.7405 5163.7099) (12691.0076 5165.9542) (12693.1145 5167.0229) (12697.8473 5167.6031)
      (12704.1679 5168.4733) (12710.4733 5170.1374) (12715.0992 5172.687) (12716.7939 5175.8321) (12715.0992 5178.9771)
      (12710.4733 5181.5267) (12704.1679 5183.1908) (12697.8473 5184.0458) (12693.1145 5184.6412) (12691.0076 5185.7099)
      (12691.7405 5187.9542) (12694.6718 5191.7099) (12698.5344 5196.7786) (12701.8168 5202.4122) (12703.2824 5207.4962)
      (12702.2595 5210.916) (12698.8397 5211.9389) (12693.7557 5210.4733) (12688.1221 5207.1908) (12683.0534 5203.3282)
      (12679.2977 5200.3969) (12677.0534 5199.6641) (12675.9847 5201.771) (12675.3893 5206.5038) (12674.5344 5212.8092)
      (12672.8702 5219.1145) (12670.3206 5223.7557) (12667.1756 5225.4504) (12664.0305 5223.7557) (12661.4809 5219.1145)
      (12659.8168 5212.8092) (12658.9618 5206.5038) (12658.3664 5201.771) (12657.2977 5199.6641) (12655.0534 5200.3969)
      (12651.2977 5203.3282) (12646.229 5207.1908) (12640.5954 5210.4733) (12635.5115 5211.9389) (12632.0916 5210.916)
      (12631.0687 5207.4962) (12632.5344 5202.4122) (12635.8168 5196.7786) (12639.6794 5191.7099) (12642.6107 5187.9542)
      (12643.3435 5185.7099) (12641.2366 5184.6412) (12636.5038 5184.0458) (12630.1832 5183.1908) (12623.8779 5181.5267)
      (12619.2519 5178.9771)
    ))
    ; P3101 -- see feature_dimensions_mm.csv
    ("06_ORNAMENT" 1 (
      (12617.5573 4864.3817) (12619.2519 4861.2366) (12623.8779 4858.687) (12630.1832 4857.0229) (12636.5038 4856.1527)
      (12641.2366 4855.5725) (12643.3435 4854.5038) (12642.6107 4852.2595) (12639.6794 4848.5038) (12635.8168 4843.4351)
      (12632.5344 4837.8015) (12631.0687 4832.7176) (12632.0916 4829.2977) (12635.5115 4828.2748) (12640.5954 4829.7405)
      (12646.229 4833.0229) (12651.2977 4836.8702) (12655.0534 4839.8015) (12657.2977 4840.5344) (12658.3664 4838.4427)
      (12658.9618 4833.7099) (12659.8168 4827.3893) (12661.4809 4821.084) (12664.0305 4816.458) (12667.1756 4814.7634)
      (12670.3206 4816.458) (12672.8702 4821.084) (12674.5344 4827.3893) (12675.3893 4833.7099) (12675.9847 4838.4427)
      (12677.0534 4840.5344) (12679.2977 4839.8015) (12683.0534 4836.8702) (12688.1221 4833.0229) (12693.7557 4829.7405)
      (12698.8397 4828.2748) (12702.2595 4829.2977) (12703.2824 4832.7176) (12701.8168 4837.8015) (12698.5344 4843.4351)
      (12694.6718 4848.5038) (12691.7405 4852.2595) (12691.0076 4854.5038) (12693.1145 4855.5725) (12697.8473 4856.1527)
      (12704.1679 4857.0229) (12710.4733 4858.687) (12715.0992 4861.2366) (12716.7939 4864.3817) (12715.0992 4867.5267)
      (12710.4733 4870.0763) (12704.1679 4871.7405) (12697.8473 4872.5954) (12693.1145 4873.1908) (12691.0076 4874.2595)
      (12691.7405 4876.5038) (12694.6718 4880.2595) (12698.5344 4885.3282) (12701.8168 4890.9618) (12703.2824 4896.0458)
      (12702.2595 4899.4656) (12698.8397 4900.4885) (12693.7557 4899.0229) (12688.1221 4895.7405) (12683.0534 4891.8779)
      (12679.2977 4888.9466) (12677.0534 4888.2137) (12675.9847 4890.3206) (12675.3893 4895.0534) (12674.5344 4901.3588)
      (12672.8702 4907.6641) (12670.3206 4912.3053) (12667.1756 4914.0) (12664.0305 4912.3053) (12661.4809 4907.6641)
      (12659.8168 4901.3588) (12658.9618 4895.0534) (12658.3664 4890.3206) (12657.2977 4888.2137) (12655.0534 4888.9466)
      (12651.2977 4891.8779) (12646.229 4895.7405) (12640.5954 4899.0229) (12635.5115 4900.4885) (12632.0916 4899.4656)
      (12631.0687 4896.0458) (12632.5344 4890.9618) (12635.8168 4885.3282) (12639.6794 4880.2595) (12642.6107 4876.5038)
      (12643.3435 4874.2595) (12641.2366 4873.1908) (12636.5038 4872.5954) (12630.1832 4871.7405) (12623.8779 4870.0763)
      (12619.2519 4867.5267)
    ))
    ; P3102 -- see feature_dimensions_mm.csv
    ("06_ORNAMENT" 1 (
      (12617.5573 4552.9313) (12619.2519 4549.7863) (12623.8779 4547.2366) (12630.1832 4545.5725) (12636.5038 4544.7023)
      (12641.2366 4544.1221) (12643.3435 4543.0534) (12642.6107 4540.8092) (12639.6794 4537.0534) (12635.8168 4531.9847)
      (12632.5344 4526.3511) (12631.0687 4521.2672) (12632.0916 4517.8473) (12635.5115 4516.8244) (12640.5954 4518.2901)
      (12646.229 4521.5725) (12651.2977 4525.4198) (12655.0534 4528.3511) (12657.2977 4529.084) (12658.3664 4526.9924)
      (12658.9618 4522.2595) (12659.8168 4515.9389) (12661.4809 4509.6336) (12664.0305 4505.0076) (12667.1756 4503.313)
      (12670.3206 4505.0076) (12672.8702 4509.6336) (12674.5344 4515.9389) (12675.3893 4522.2595) (12675.9847 4526.9924)
      (12677.0534 4529.084) (12679.2977 4528.3511) (12683.0534 4525.4198) (12688.1221 4521.5725) (12693.7557 4518.2901)
      (12698.8397 4516.8244) (12702.2595 4517.8473) (12703.2824 4521.2672) (12701.8168 4526.3511) (12698.5344 4531.9847)
      (12694.6718 4537.0534) (12691.7405 4540.8092) (12691.0076 4543.0534) (12693.1145 4544.1221) (12697.8473 4544.7023)
      (12704.1679 4545.5725) (12710.4733 4547.2366) (12715.0992 4549.7863) (12716.7939 4552.9313) (12715.0992 4556.0763)
      (12710.4733 4558.626) (12704.1679 4560.2901) (12697.8473 4561.145) (12693.1145 4561.7405) (12691.0076 4562.8092)
      (12691.7405 4565.0534) (12694.6718 4568.8092) (12698.5344 4573.8779) (12701.8168 4579.5115) (12703.2824 4584.5954)
      (12702.2595 4588.0153) (12698.8397 4589.0382) (12693.7557 4587.5725) (12688.1221 4584.2901) (12683.0534 4580.4275)
      (12679.2977 4577.4962) (12677.0534 4576.7634) (12675.9847 4578.8702) (12675.3893 4583.6031) (12674.5344 4589.9084)
      (12672.8702 4596.2137) (12670.3206 4600.855) (12667.1756 4602.5496) (12664.0305 4600.855) (12661.4809 4596.2137)
      (12659.8168 4589.9084) (12658.9618 4583.6031) (12658.3664 4578.8702) (12657.2977 4576.7634) (12655.0534 4577.4962)
      (12651.2977 4580.4275) (12646.229 4584.2901) (12640.5954 4587.5725) (12635.5115 4589.0382) (12632.0916 4588.0153)
      (12631.0687 4584.5954) (12632.5344 4579.5115) (12635.8168 4573.8779) (12639.6794 4568.8092) (12642.6107 4565.0534)
      (12643.3435 4562.8092) (12641.2366 4561.7405) (12636.5038 4561.145) (12630.1832 4560.2901) (12623.8779 4558.626)
      (12619.2519 4556.0763)
    ))
    ; P3103 -- see feature_dimensions_mm.csv
    ("06_ORNAMENT" 1 (
      (12617.5573 4241.4809) (12619.2519 4238.3359) (12623.8779 4235.7863) (12630.1832 4234.1221) (12636.5038 4233.2519)
      (12641.2366 4232.6718) (12643.3435 4231.6031) (12642.6107 4229.3588) (12639.6794 4225.6031) (12635.8168 4220.5344)
      (12632.5344 4214.9008) (12631.0687 4209.8168) (12632.0916 4206.3969) (12635.5115 4205.374) (12640.5954 4206.8397)
      (12646.229 4210.1221) (12651.2977 4213.9695) (12655.0534 4216.9008) (12657.2977 4217.6336) (12658.3664 4215.542)
      (12658.9618 4210.8092) (12659.8168 4204.4885) (12661.4809 4198.1832) (12664.0305 4193.5573) (12667.1756 4191.8626)
      (12670.3206 4193.5573) (12672.8702 4198.1832) (12674.5344 4204.4885) (12675.3893 4210.8092) (12675.9847 4215.542)
      (12677.0534 4217.6336) (12679.2977 4216.9008) (12683.0534 4213.9695) (12688.1221 4210.1221) (12693.7557 4206.8397)
      (12698.8397 4205.374) (12702.2595 4206.3969) (12703.2824 4209.8168) (12701.8168 4214.9008) (12698.5344 4220.5344)
      (12694.6718 4225.6031) (12691.7405 4229.3588) (12691.0076 4231.6031) (12693.1145 4232.6718) (12697.8473 4233.2519)
      (12704.1679 4234.1221) (12710.4733 4235.7863) (12715.0992 4238.3359) (12716.7939 4241.4809) (12715.0992 4244.626)
      (12710.4733 4247.1756) (12704.1679 4248.8397) (12697.8473 4249.6947) (12693.1145 4250.2901) (12691.0076 4251.3588)
      (12691.7405 4253.6031) (12694.6718 4257.3588) (12698.5344 4262.4275) (12701.8168 4268.0611) (12703.2824 4273.145)
      (12702.2595 4276.5649) (12698.8397 4277.5878) (12693.7557 4276.1221) (12688.1221 4272.8397) (12683.0534 4268.9771)
      (12679.2977 4266.0458) (12677.0534 4265.313) (12675.9847 4267.4198) (12675.3893 4272.1527) (12674.5344 4278.458)
      (12672.8702 4284.7634) (12670.3206 4289.4046) (12667.1756 4291.0992) (12664.0305 4289.4046) (12661.4809 4284.7634)
      (12659.8168 4278.458) (12658.9618 4272.1527) (12658.3664 4267.4198) (12657.2977 4265.313) (12655.0534 4266.0458)
      (12651.2977 4268.9771) (12646.229 4272.8397) (12640.5954 4276.1221) (12635.5115 4277.5878) (12632.0916 4276.5649)
      (12631.0687 4273.145) (12632.5344 4268.0611) (12635.8168 4262.4275) (12639.6794 4257.3588) (12642.6107 4253.6031)
      (12643.3435 4251.3588) (12641.2366 4250.2901) (12636.5038 4249.6947) (12630.1832 4248.8397) (12623.8779 4247.1756)
      (12619.2519 4244.626)
    ))
    ; P3104 -- see feature_dimensions_mm.csv
    ("06_ORNAMENT" 1 (
      (12617.5573 3930.0305) (12619.2519 3926.8855) (12623.8779 3924.3359) (12630.1832 3922.6718) (12636.5038 3921.8015)
      (12641.2366 3921.2214) (12643.3435 3920.1527) (12642.6107 3917.9084) (12639.6794 3914.1527) (12635.8168 3909.084)
      (12632.5344 3903.4504) (12631.0687 3898.3664) (12632.0916 3894.9466) (12635.5115 3893.9237) (12640.5954 3895.3893)
      (12646.229 3898.6718) (12651.2977 3902.5191) (12655.0534 3905.4504) (12657.2977 3906.1832) (12658.3664 3904.0916)
      (12658.9618 3899.3588) (12659.8168 3893.0382) (12661.4809 3886.7328) (12664.0305 3882.1069) (12667.1756 3880.4122)
      (12670.3206 3882.1069) (12672.8702 3886.7328) (12674.5344 3893.0382) (12675.3893 3899.3588) (12675.9847 3904.0916)
      (12677.0534 3906.1832) (12679.2977 3905.4504) (12683.0534 3902.5191) (12688.1221 3898.6718) (12693.7557 3895.3893)
      (12698.8397 3893.9237) (12702.2595 3894.9466) (12703.2824 3898.3664) (12701.8168 3903.4504) (12698.5344 3909.084)
      (12694.6718 3914.1527) (12691.7405 3917.9084) (12691.0076 3920.1527) (12693.1145 3921.2214) (12697.8473 3921.8015)
      (12704.1679 3922.6718) (12710.4733 3924.3359) (12715.0992 3926.8855) (12716.7939 3930.0305) (12715.0992 3933.1756)
      (12710.4733 3935.7252) (12704.1679 3937.3893) (12697.8473 3938.2443) (12693.1145 3938.8397) (12691.0076 3939.9084)
      (12691.7405 3942.1527) (12694.6718 3945.9084) (12698.5344 3950.9771) (12701.8168 3956.6107) (12703.2824 3961.6947)
      (12702.2595 3965.1145) (12698.8397 3966.1374) (12693.7557 3964.6718) (12688.1221 3961.3893) (12683.0534 3957.5267)
      (12679.2977 3954.5954) (12677.0534 3953.8626) (12675.9847 3955.9695) (12675.3893 3960.7023) (12674.5344 3967.0076)
      (12672.8702 3973.313) (12670.3206 3977.9542) (12667.1756 3979.6489) (12664.0305 3977.9542) (12661.4809 3973.313)
      (12659.8168 3967.0076) (12658.9618 3960.7023) (12658.3664 3955.9695) (12657.2977 3953.8626) (12655.0534 3954.5954)
      (12651.2977 3957.5267) (12646.229 3961.3893) (12640.5954 3964.6718) (12635.5115 3966.1374) (12632.0916 3965.1145)
      (12631.0687 3961.6947) (12632.5344 3956.6107) (12635.8168 3950.9771) (12639.6794 3945.9084) (12642.6107 3942.1527)
      (12643.3435 3939.9084) (12641.2366 3938.8397) (12636.5038 3938.2443) (12630.1832 3937.3893) (12623.8779 3935.7252)
      (12619.2519 3933.1756)
    ))
    ; P3105 -- see feature_dimensions_mm.csv
    ("06_ORNAMENT" 1 (
      (12625.9542 1740.458) (12627.4198 1725.5725) (12631.771 1711.2519) (12638.8244 1698.0458) (12648.3053 1686.4733)
      (12659.8779 1676.9924) (12673.084 1669.9389) (12687.4046 1665.5878) (12702.2901 1664.1221) (12717.1756 1665.5878)
      (12731.4962 1669.9389) (12744.7023 1676.9924) (12756.2748 1686.4733) (12765.7557 1698.0458) (12772.8092 1711.2519)
      (12777.1603 1725.5725) (12778.626 1740.458) (12777.1603 1755.3435) (12772.8092 1769.6641) (12765.7557 1782.8702)
      (12756.2748 1794.4427) (12744.7023 1803.9237) (12731.4962 1810.9771) (12717.1756 1815.3282) (12702.2901 1816.7939)
      (12687.4046 1815.3282) (12673.084 1810.9771) (12659.8779 1803.9237) (12648.3053 1794.4427) (12638.8244 1782.8702)
      (12631.771 1769.6641) (12627.4198 1755.3435)
    ))
    ; P3106 -- see feature_dimensions_mm.csv
    ("06_ORNAMENT" 1 (
      (12648.855 5253.6947) (12667.1756 5233.084) (12685.4962 5253.6947) (12667.1756 5274.3053)
    ))
    ; P3107 -- see feature_dimensions_mm.csv
    ("06_ORNAMENT" 1 (
      (12648.855 4942.2443) (12667.1756 4921.6336) (12685.4962 4942.2443) (12667.1756 4962.855)
    ))
    ; P3108 -- see feature_dimensions_mm.csv
    ("06_ORNAMENT" 1 (
      (12648.855 4630.7939) (12667.1756 4610.1832) (12685.4962 4630.7939) (12667.1756 4651.4046)
    ))
    ; P3109 -- see feature_dimensions_mm.csv
    ("06_ORNAMENT" 1 (
      (12648.855 4319.3435) (12667.1756 4298.7328) (12685.4962 4319.3435) (12667.1756 4339.9542)
    ))
    ; P3110 -- see feature_dimensions_mm.csv
    ("06_ORNAMENT" 1 (
      (12648.855 4007.8931) (12667.1756 3987.2824) (12685.4962 4007.8931) (12667.1756 4028.5038)
    ))
    ; P3111 -- see feature_dimensions_mm.csv
    ("06_ORNAMENT" 1 (
      (12655.2672 5175.8321) (12656.1679 5171.2672) (12658.7481 5167.4046) (12662.626 5164.8244) (12667.1756 5163.9237)
      (12671.7252 5164.8244) (12675.6031 5167.4046) (12678.1832 5171.2672) (12679.084 5175.8321) (12678.1832 5180.3817)
      (12675.6031 5184.2443) (12671.7252 5186.8244) (12667.1756 5187.7405) (12662.626 5186.8244) (12658.7481 5184.2443)
      (12656.1679 5180.3817)
    ))
    ; P3112 -- see feature_dimensions_mm.csv
    ("06_ORNAMENT" 1 (
      (12655.2672 4864.3817) (12656.1679 4859.8168) (12658.7481 4855.9542) (12662.626 4853.374) (12667.1756 4852.4733)
      (12671.7252 4853.374) (12675.6031 4855.9542) (12678.1832 4859.8168) (12679.084 4864.3817) (12678.1832 4868.9313)
      (12675.6031 4872.7939) (12671.7252 4875.374) (12667.1756 4876.2901) (12662.626 4875.374) (12658.7481 4872.7939)
      (12656.1679 4868.9313)
    ))
    ; P3113 -- see feature_dimensions_mm.csv
    ("06_ORNAMENT" 1 (
      (12655.2672 4552.9313) (12656.1679 4548.3664) (12658.7481 4544.5038) (12662.626 4541.9237) (12667.1756 4541.0229)
      (12671.7252 4541.9237) (12675.6031 4544.5038) (12678.1832 4548.3664) (12679.084 4552.9313) (12678.1832 4557.4809)
      (12675.6031 4561.3435) (12671.7252 4563.9237) (12667.1756 4564.8397) (12662.626 4563.9237) (12658.7481 4561.3435)
      (12656.1679 4557.4809)
    ))
    ; P3114 -- see feature_dimensions_mm.csv
    ("06_ORNAMENT" 1 (
      (12655.2672 4241.4809) (12656.1679 4236.916) (12658.7481 4233.0534) (12662.626 4230.4733) (12667.1756 4229.5725)
      (12671.7252 4230.4733) (12675.6031 4233.0534) (12678.1832 4236.916) (12679.084 4241.4809) (12678.1832 4246.0305)
      (12675.6031 4249.8931) (12671.7252 4252.4733) (12667.1756 4253.3893) (12662.626 4252.4733) (12658.7481 4249.8931)
      (12656.1679 4246.0305)
    ))
    ; P3115 -- see feature_dimensions_mm.csv
    ("06_ORNAMENT" 1 (
      (12655.2672 3930.0305) (12656.1679 3925.4656) (12658.7481 3921.6031) (12662.626 3919.0229) (12667.1756 3918.1221)
      (12671.7252 3919.0229) (12675.6031 3921.6031) (12678.1832 3925.4656) (12679.084 3930.0305) (12678.1832 3934.5802)
      (12675.6031 3938.4427) (12671.7252 3941.0229) (12667.1756 3941.9389) (12662.626 3941.0229) (12658.7481 3938.4427)
      (12656.1679 3934.5802)
    ))
    ; P3116 -- see feature_dimensions_mm.csv
    ("06_ORNAMENT" 1 (
      (12662.2137 1972.6412) (12663.8015 1952.1832) (12667.2519 1932.2137) (12672.7023 1912.9924) (12680.2748 1894.8092)
      (12690.1069 1877.9237) (12702.2901 1862.5954) (12714.4733 1878.9924) (12724.3053 1896.855) (12731.8779 1915.9084)
      (12737.3282 1935.8473) (12740.7786 1956.3969) (12742.3664 1977.2824) (12742.1985 1998.1985) (12740.3969 2018.9008)
      (12737.084 2039.0687) (12732.3969 2058.4275) (12726.458 2076.7023) (12719.374 2093.5878) (12711.2824 2108.8397)
      (12702.2901 2122.1374) (12693.2977 2107.3282) (12685.2061 2090.8702) (12678.1221 2073.0382) (12672.1832 2054.1069)
      (12667.4962 2034.3359) (12664.1832 2013.9847) (12662.3817 1993.3435)
    ))
    ; P3117 -- see feature_dimensions_mm.csv
    ("06_ORNAMENT" 1 (
      (12662.2137 1503.6336) (12662.3817 1482.7023) (12664.1832 1462.0153) (12667.4962 1441.8473) (12672.1832 1422.4885)
      (12678.1221 1404.2137) (12685.2061 1387.313) (12693.2977 1372.0763) (12702.2901 1358.7786) (12711.2824 1373.5878)
      (12719.374 1390.0458) (12726.458 1407.8779) (12732.3969 1426.8092) (12737.084 1446.5802) (12740.3969 1466.916)
      (12742.1985 1487.5725) (12742.3664 1508.2748) (12740.7786 1528.7328) (12737.3282 1548.7023) (12731.8779 1567.9237)
      (12724.3053 1586.1069) (12714.4733 1602.9924) (12702.2901 1618.3206) (12690.1069 1601.9237) (12680.2748 1584.0611)
      (12672.7023 1565.0076) (12667.2519 1545.0687) (12663.8015 1524.5191)
    ))
    ; P3118 -- see feature_dimensions_mm.csv
    ("06_ORNAMENT" 1 (
      (12684.9924 5705.9084) (12685.8626 5697.2977) (12689.6794 5695.8931) (12691.1145 5695.3282) (12738.5802 5675.9542)
      (12740.2443 5675.2366) (12783.4656 5655.5725) (12780.0916 5662.3664) (12768.6107 5681.3282) (12755.6336 5698.9313)
      (12741.145 5714.8397) (12739.9695 5715.8779) (12743.8626 5714.0) (12764.9008 5706.6565) (12786.7481 5701.3435)
      (12809.1145 5697.9542) (12831.6489 5696.4122) (12854.0763 5696.5802) (12876.0611 5698.3664) (12897.2824 5701.6641)
      (12917.4351 5706.3817) (12936.1985 5712.3817) (12953.2519 5719.5878) (12968.2901 5727.8931) (12953.0687 5738.5038)
      (12936.0 5748.3359) (12917.374 5757.2214) (12897.4656 5765.0076) (12876.5649 5771.542) (12854.916 5776.6718)
      (12832.8244 5780.2595) (12810.5649 5782.1527) (12788.3969 5782.1985) (12766.626 5780.229) (12745.4962 5776.1221)
      (12725.313 5769.6947) (12706.3359 5760.8244) (12688.855 5749.3435) (12685.4656 5727.771)
    ))
    ; P3119 -- see feature_dimensions_mm.csv
    ("06_ORNAMENT" 1 (
      (12695.4198 5020.1069) (12697.1145 5016.9618) (12701.7405 5014.4122) (12708.0458 5012.7481) (12714.3664 5011.8779)
      (12719.0992 5011.2977) (12721.2061 5010.229) (12720.4733 5007.9847) (12717.542 5004.229) (12713.6794 4999.1603)
      (12710.3969 4993.5267) (12708.9313 4988.4427) (12709.9542 4985.0229) (12713.374 4984.0) (12718.458 4985.4656)
      (12724.0916 4988.7481) (12729.1603 4992.5954) (12732.916 4995.5267) (12735.1603 4996.2595) (12736.229 4994.1679)
      (12736.8244 4989.4351) (12737.6794 4983.1145) (12739.3435 4976.8092) (12741.8931 4972.1832) (12745.0382 4970.4885)
      (12748.1832 4972.1832) (12750.7328 4976.8092) (12752.3969 4983.1145) (12753.2519 4989.4351) (12753.8473 4994.1679)
      (12754.916 4996.2595) (12757.1603 4995.5267) (12760.916 4992.5954) (12765.9847 4988.7481) (12771.6183 4985.4656)
      (12776.7023 4984.0) (12778.626 4984.5649) (12778.626 4995.3282) (12776.3969 4999.1603) (12772.5344 5004.229)
      (12769.6031 5007.9847) (12768.8702 5010.229) (12770.9771 5011.2977) (12775.7099 5011.8779) (12778.626 5012.2901)
      (12778.626 5027.9237) (12775.7099 5028.3206) (12770.9771 5028.916) (12768.8702 5029.9847) (12769.6031 5032.229)
      (12772.5344 5035.9847) (12776.3969 5041.0534) (12778.626 5044.8855) (12778.626 5055.6336) (12776.7023 5056.2137)
      (12771.6183 5054.7481) (12765.9847 5051.4656) (12760.916 5047.6031) (12757.1603 5044.6718) (12754.916 5043.9389)
      (12753.8473 5046.0458) (12753.2519 5050.7786) (12752.3969 5057.084) (12750.7328 5063.3893) (12748.1832 5068.0305)
      (12745.0382 5069.7252) (12741.8931 5068.0305) (12739.3435 5063.3893) (12737.6794 5057.084) (12736.8244 5050.7786)
      (12736.229 5046.0458) (12735.1603 5043.9389) (12732.916 5044.6718) (12729.1603 5047.6031) (12724.0916 5051.4656)
      (12718.458 5054.7481) (12713.374 5056.2137) (12709.9542 5055.1908) (12708.9313 5051.771) (12710.3969 5046.687)
      (12713.6794 5041.0534) (12717.542 5035.9847) (12720.4733 5032.229) (12721.2061 5029.9847) (12719.0992 5028.916)
      (12714.3664 5028.3206) (12708.0458 5027.4656) (12701.7405 5025.8015) (12697.1145 5023.2519)
    ))
    ; P3120 -- see feature_dimensions_mm.csv
    ("06_ORNAMENT" 1 (
      (12695.4198 4708.6565) (12697.1145 4705.5115) (12701.7405 4702.9618) (12708.0458 4701.2977) (12714.3664 4700.4275)
      (12719.0992 4699.8473) (12721.2061 4698.7786) (12720.4733 4696.5344) (12717.542 4692.7786) (12713.6794 4687.7099)
      (12710.3969 4682.0763) (12708.9313 4676.9924) (12709.9542 4673.5725) (12713.374 4672.5496) (12718.458 4674.0153)
      (12724.0916 4677.2977) (12729.1603 4681.145) (12732.916 4684.0763) (12735.1603 4684.8092) (12736.229 4682.7176)
      (12736.8244 4677.9847) (12737.6794 4671.6641) (12739.3435 4665.3588) (12741.8931 4660.7328) (12745.0382 4659.0382)
      (12748.1832 4660.7328) (12750.7328 4665.3588) (12752.3969 4671.6641) (12753.2519 4677.9847) (12753.8473 4682.7176)
      (12754.916 4684.8092) (12757.1603 4684.0763) (12760.916 4681.145) (12765.9847 4677.2977) (12771.6183 4674.0153)
      (12776.7023 4672.5496) (12778.626 4673.1145) (12778.626 4683.8779) (12776.3969 4687.7099) (12772.5344 4692.7786)
      (12769.6031 4696.5344) (12768.8702 4698.7786) (12770.9771 4699.8473) (12775.7099 4700.4275) (12778.626 4700.8397)
      (12778.626 4716.4733) (12775.7099 4716.8702) (12770.9771 4717.4656) (12768.8702 4718.5344) (12769.6031 4720.7786)
      (12772.5344 4724.5344) (12776.3969 4729.6031) (12778.626 4733.4351) (12778.626 4744.1832) (12776.7023 4744.7634)
      (12771.6183 4743.2977) (12765.9847 4740.0153) (12760.916 4736.1527) (12757.1603 4733.2214) (12754.916 4732.4885)
      (12753.8473 4734.5954) (12753.2519 4739.3282) (12752.3969 4745.6336) (12750.7328 4751.9389) (12748.1832 4756.5802)
      (12745.0382 4758.2748) (12741.8931 4756.5802) (12739.3435 4751.9389) (12737.6794 4745.6336) (12736.8244 4739.3282)
      (12736.229 4734.5954) (12735.1603 4732.4885) (12732.916 4733.2214) (12729.1603 4736.1527) (12724.0916 4740.0153)
      (12718.458 4743.2977) (12713.374 4744.7634) (12709.9542 4743.7405) (12708.9313 4740.3206) (12710.3969 4735.2366)
      (12713.6794 4729.6031) (12717.542 4724.5344) (12720.4733 4720.7786) (12721.2061 4718.5344) (12719.0992 4717.4656)
      (12714.3664 4716.8702) (12708.0458 4716.0153) (12701.7405 4714.3511) (12697.1145 4711.8015)
    ))
    ; P3121 -- see feature_dimensions_mm.csv
    ("06_ORNAMENT" 1 (
      (12726.7176 5097.9695) (12745.0382 5077.3588) (12763.3588 5097.9695) (12745.0382 5118.5802)
    ))
    ; P3122 -- see feature_dimensions_mm.csv
    ("06_ORNAMENT" 1 (
      (12726.7176 4786.5191) (12745.0382 4765.9084) (12763.3588 4786.5191) (12745.0382 4807.1298)
    ))
    ; P3123 -- see feature_dimensions_mm.csv
    ("06_ORNAMENT" 1 (
      (12726.7176 4163.6183) (12745.0382 4143.0076) (12763.3588 4163.6183) (12745.0382 4184.229)
    ))
    ; P3124 -- see feature_dimensions_mm.csv
    ("06_ORNAMENT" 1 (
      (12726.7176 3852.1679) (12744.5954 3832.0611) (12745.4809 3832.0611) (12763.3588 3852.1679) (12745.0382 3872.7786)
    ))
    ; P3125 -- see feature_dimensions_mm.csv
    ("06_ORNAMENT" 1 (
      (12732.8244 3007.6336) (12763.3588 2977.0992) (12793.8931 3007.6336) (12763.3588 3038.1679)
    ))
    ; P3126 -- see feature_dimensions_mm.csv
    ("06_ORNAMENT" 1 (
      (12732.8244 2916.0305) (12763.3588 2885.4962) (12793.8931 2916.0305) (12763.3588 2946.5649)
    ))
    ; P3127 -- see feature_dimensions_mm.csv
    ("06_ORNAMENT" 1 (
      (12733.1298 5020.1069) (12734.0305 5015.542) (12736.6107 5011.6794) (12740.4885 5009.0992) (12745.0382 5008.1985)
      (12749.5878 5009.0992) (12753.4656 5011.6794) (12756.0458 5015.542) (12756.9466 5020.1069) (12756.0458 5024.6565)
      (12753.4656 5028.5191) (12749.5878 5031.0992) (12745.0382 5032.0153) (12740.4885 5031.0992) (12736.6107 5028.5191)
      (12734.0305 5024.6565)
    ))
    ; P3128 -- see feature_dimensions_mm.csv
    ("06_ORNAMENT" 1 (
      (12733.1298 4708.6565) (12734.0305 4704.0916) (12736.6107 4700.229) (12740.4885 4697.6489) (12745.0382 4696.7481)
      (12749.5878 4697.6489) (12753.4656 4700.229) (12756.0458 4704.0916) (12756.9466 4708.6565) (12756.0458 4713.2061)
      (12753.4656 4717.0687) (12749.5878 4719.6489) (12745.0382 4720.5649) (12740.4885 4719.6489) (12736.6107 4717.0687)
      (12734.0305 4713.2061)
    ))
    ; P3129 -- see feature_dimensions_mm.csv
    ("06_ORNAMENT" 1 (
      (12733.1298 4397.2061) (12734.0305 4392.6412) (12736.6107 4388.7786) (12740.4885 4386.1985) (12745.0382 4385.2977)
      (12749.5878 4386.1985) (12753.4656 4388.7786) (12756.0458 4392.6412) (12756.9466 4397.2061) (12756.0458 4401.7557)
      (12753.4656 4405.6183) (12749.5878 4408.1985) (12745.0382 4409.1145) (12740.4885 4408.1985) (12736.6107 4405.6183)
      (12734.0305 4401.7557)
    ))
    ; P3130 -- see feature_dimensions_mm.csv
    ("06_ORNAMENT" 1 (
      (12733.1298 4085.7557) (12734.0305 4081.1908) (12736.6107 4077.3282) (12740.4885 4074.7481) (12745.0382 4073.8473)
      (12749.5878 4074.7481) (12753.4656 4077.3282) (12756.0458 4081.1908) (12756.9466 4085.7557) (12756.0458 4090.3053)
      (12753.4656 4094.1679) (12749.5878 4096.7481) (12745.0382 4097.6641) (12740.4885 4096.7481) (12736.6107 4094.1679)
      (12734.0305 4090.3053)
    ))
    ; P3131 -- see feature_dimensions_mm.csv
    ("06_ORNAMENT" 1 (
      (12748.0916 2839.6947) (12778.626 2839.6947) (12763.3588 2854.9618)
    ))
    ; P3132 -- see feature_dimensions_mm.csv
    ("06_ORNAMENT" 1 (
      (12760.4122 1885.145) (12760.4733 1865.6031) (12763.3588 1846.229) (12782.1069 1854.3359) (12799.5573 1864.9008)
      (12815.6336 1877.6031) (12830.3206 1892.1527) (12843.6031 1908.2137) (12855.4046 1925.5115) (12865.7252 1943.7252)
      (12874.5038 1962.5344) (12881.7252 1981.6641) (12887.3435 2000.7634) (12891.3435 2019.5725) (12893.6489 2037.7405)
      (12894.2595 2054.9924) (12893.1298 2071.0076) (12877.9389 2062.6718) (12862.7023 2052.458) (12847.6641 2040.5649)
      (12833.0382 2027.145) (12819.0992 2012.3664) (12806.0611 1996.3969) (12794.1679 1979.4046) (12783.6794 1961.5725)
      (12774.8092 1943.0687) (12767.8168 1924.0458) (12762.9466 1904.6718)
    ))
    ; P3133 -- see feature_dimensions_mm.csv
    ("06_ORNAMENT" 1 (
      (12761.0076 1614.3817) (12761.4351 1594.0) (12764.3969 1573.7252) (12769.6336 1553.7252) (12776.916 1534.1985)
      (12786.0 1515.3282) (12796.6107 1497.2824) (12808.5038 1480.2748) (12821.4504 1464.458) (12835.1908 1450.0305)
      (12849.4809 1437.1908) (12864.0611 1426.0916) (12878.7023 1416.9466) (12893.1298 1409.9084) (12893.5115 1427.2366)
      (12892.2901 1445.5267) (12889.5115 1464.5191) (12885.1908 1483.8779) (12879.374 1503.3435) (12872.0611 1522.626)
      (12863.2824 1541.4046) (12853.084 1559.4198) (12841.4962 1576.3511) (12828.5038 1591.9084) (12814.1832 1605.8321)
      (12798.5344 1617.7863) (12781.5725 1627.4962) (12763.3588 1634.687)
    ))
    ; P3134 -- see feature_dimensions_mm.csv
    ("06_ORNAMENT" 1 (
      (12773.2824 5175.8321) (12774.9771 5172.687) (12778.626 5170.6718) (12778.626 5180.9924) (12774.9771 5178.9771)
    ))
    ; P3135 -- see feature_dimensions_mm.csv
    ("06_ORNAMENT" 1 (
      (12773.2824 4552.9313) (12774.9771 4549.7863) (12778.626 4547.771) (12778.626 4558.0916) (12774.9771 4556.0763)
    ))
    ; P3136 -- see feature_dimensions_mm.csv
    ("06_ORNAMENT" 1 (
      (12773.2824 3930.0305) (12774.9771 3926.8855) (12778.626 3924.8702) (12778.626 3935.1908) (12774.9771 3933.1756)
    ))
    ; P3137 -- see feature_dimensions_mm.csv
    ("06_ORNAMENT" 1 (
      (12777.5267 2110.4122) (12778.0763 2098.5649) (12780.1221 2086.9466) (12783.8015 2075.6794) (12789.2214 2064.8855)
      (12799.4656 2072.1374) (12808.4427 2080.6107) (12816.1527 2090.1374) (12822.6565 2100.5344) (12827.9847 2111.6336)
      (12832.1679 2123.2214) (12835.2519 2135.145) (12837.2519 2147.2061) (12838.229 2159.2214) (12838.1832 2171.0229)
      (12837.1908 2182.4275) (12835.2519 2193.2366) (12832.4275 2203.2672) (12828.7328 2212.3664) (12820.7634 2205.4809)
      (12813.1145 2197.5115) (12805.8931 2188.5802) (12799.2214 2178.8397) (12793.2366 2168.4122) (12788.0305 2157.4046)
      (12783.7405 2145.9847) (12780.4885 2134.2595) (12778.3817 2122.3511)
    ))
    ; P3138 -- see feature_dimensions_mm.csv
    ("06_ORNAMENT" 1 (
      (12778.0916 1368.4275) (12779.0229 1356.1679) (12781.1908 1344.0305) (12784.4885 1332.1679) (12788.7786 1320.7176)
      (12793.9542 1309.8321) (12799.8779 1299.6183) (12806.4427 1290.2595) (12813.5267 1281.8626) (12820.9924 1274.5802)
      (12828.7328 1268.5496) (12832.1985 1278.5038) (12834.8397 1289.2366) (12836.626 1300.5649) (12837.5267 1312.3359)
      (12837.5115 1324.3664) (12836.5038 1336.5038) (12834.5038 1348.5344) (12831.4656 1360.3206) (12827.3435 1371.6794)
      (12822.1069 1382.4427) (12815.7099 1392.4275) (12808.1221 1401.4656) (12799.313 1409.3893) (12789.2214 1416.0305)
      (12783.9695 1404.626) (12780.4427 1392.8092) (12778.5191 1380.687)
    ))
    ; P3139 -- see feature_dimensions_mm.csv
    ("06_ORNAMENT" 1 (
      (12808.0611 1801.5267) (12828.3664 1799.1756) (12848.7481 1799.6031) (12869.0229 1802.5649) (12889.0229 1807.8015)
      (12908.5496 1815.084) (12927.4198 1824.1679) (12945.4656 1834.7786) (12962.4733 1846.6718) (12978.2901 1859.6183)
      (12992.7176 1873.3588) (13005.5573 1887.6489) (13016.6565 1902.229) (13025.8015 1916.8702) (13032.8397 1931.2977)
      (13015.5115 1931.6794) (12997.2214 1930.458) (12978.229 1927.6794) (12958.8702 1923.3588) (12939.4046 1917.542)
      (12920.1221 1910.229) (12901.3435 1901.4504) (12883.3282 1891.2519) (12866.3969 1879.6641) (12850.8397 1866.6718)
      (12836.916 1852.3511) (12824.9618 1836.7023) (12815.2519 1819.7405)
    ))
    ; P3140 -- see feature_dimensions_mm.csv
    ("06_ORNAMENT" 1 (
      (12808.0611 1679.3893) (12816.1679 1660.6412) (12826.7328 1643.1908) (12839.4351 1627.1145) (12853.9847 1612.4275)
      (12870.0458 1599.145) (12887.3435 1587.3435) (12905.5573 1577.0229) (12924.3664 1568.2443) (12943.4962 1561.0229)
      (12962.5954 1555.4046) (12981.4046 1551.4046) (12999.5725 1549.0992) (13016.8244 1548.4885) (13032.8397 1549.6183)
      (13024.5038 1564.8092) (13014.2901 1580.0458) (13002.3969 1595.084) (12988.9771 1609.7099) (12974.1985 1623.6489)
      (12958.229 1636.687) (12941.2519 1648.5802) (12923.4046 1659.0687) (12904.9008 1667.9389) (12885.8779 1674.9313)
      (12866.5038 1679.8015) (12846.9771 1682.3359) (12827.4351 1682.2748)
    ))
    ; P3141 -- see feature_dimensions_mm.csv
    ("06_ORNAMENT" 1 (
      (12824.4275 1740.458) (12840.8244 1728.2748) (12858.687 1718.4427) (12877.7405 1710.8702) (12897.6794 1705.4198)
      (12918.229 1701.9695) (12939.1145 1700.3817) (12960.0458 1700.5496) (12980.7328 1702.3511) (13000.9008 1705.6641)
      (13020.2595 1710.3511) (13038.5344 1716.2901) (13055.4351 1723.374) (13070.6718 1731.4656) (13083.9695 1740.458)
      (13069.1603 1749.4504) (13052.7023 1757.542) (13034.8702 1764.626) (13015.9389 1770.5649) (12996.1679 1775.2519)
      (12975.8321 1778.5649) (12955.1756 1780.3664) (12934.4733 1780.5344) (12914.0153 1778.9466) (12894.0458 1775.4962)
      (12874.8244 1770.0458) (12856.6412 1762.4733) (12839.7557 1752.6412)
    ))
    ; P3142 -- see feature_dimensions_mm.csv
    ("06_ORNAMENT" 1 (
      (12877.0534 5604.0153) (12909.2672 5582.1221) (12912.3206 5579.8473) (12930.1221 5565.4656) (12926.0763 5572.1527)
      (12925.1298 5573.3893) (12928.5954 5570.8092) (12947.7863 5559.4962) (12968.1832 5550.0153) (12989.4504 5542.3359)
      (13011.2672 5536.4122) (13033.2824 5532.2137) (13055.1908 5529.6794) (13076.6565 5528.7786) (13078.5038 5528.8397)
      (13076.8855 5526.7176) (13070.7786 5511.9847) (13068.7023 5496.1832) (13070.7786 5480.3817) (13076.8855 5465.6489)
      (13085.0076 5455.0534) (13084.1527 5455.1298) (13063.2214 5454.1985) (13059.3435 5453.4504) (13056.6565 5455.2824)
      (13038.1679 5465.6489) (13041.6641 5448.626) (13031.2824 5431.6489) (13029.7252 5428.1069) (13032.458 5419.7863)
      (13033.7252 5415.1603) (13034.4885 5410.4275) (13037.8931 5378.9924) (13038.1679 5374.0458) (13038.1679 5211.7099)
      (13043.9237 5200.1985) (13053.6489 5184.4427) (13064.1374 5170.8397) (13072.3053 5187.5115) (13079.4198 5205.8779)
      (13085.3435 5225.6336) (13090.0 5246.5038) (13093.2672 5268.1679) (13095.0382 5290.3359) (13095.2214 5312.7176)
      (13094.9466 5316.5954) (13095.2519 5316.0305) (13110.7481 5290.687) (13127.6489 5266.229) (13145.8321 5243.084)
      (13149.374 5239.1603) (13138.7634 5223.9847) (13136.8855 5220.4427) (13129.771 5221.374) (13113.9695 5219.2977)
      (13099.2366 5213.1908) (13086.5954 5203.4809) (13076.8855 5190.8397) (13070.7786 5176.1069) (13068.7023 5160.3053)
      (13070.7786 5144.5038) (13076.8855 5129.771) (13086.5954 5117.1298) (13099.2366 5107.4198) (13106.5954 5104.3664)
      (13106.2748 5095.1603) (13106.8244 5080.6718) (13095.8626 5090.5038) (13076.0153 5106.229) (13056.6565 5119.4046)
      (13038.1679 5129.771) (13042.8244 5107.0687) (13049.5878 5082.9466) (13058.3206 5057.8168) (13068.916 5032.0458)
      (13081.2672 5006.0305) (13095.2519 4980.1527) (13110.7481 4954.8092) (13127.6489 4930.3511) (13145.8321 4907.2061)
      (13156.1527 4895.7405) (13153.6489 4880.0763) (13145.5725 4883.4198) (13129.771 4885.4962) (13113.9695 4883.4198)
      (13099.2366 4877.313) (13086.5954 4867.6031) (13076.8855 4854.9618) (13070.7786 4840.229) (13068.7023 4824.4275)
      (13070.7786 4808.626) (13076.8855 4793.8931) (13086.5954 4781.2519) (13099.2366 4771.542) (13113.9695 4765.4351)
      (13129.771 4763.3588) (13145.5725 4765.4351) (13160.3053 4771.542) (13172.9466 4781.2519) (13182.6565 4793.8931)
      (13188.5344 4808.0763) (13200.5191 4822.7634) (13212.7939 4840.2595) (13215.145 4844.1527) (13229.0534 4835.2977)
      (13251.9084 4824.4275) (13248.626 4850.8855) (13242.1679 4877.6641) (13238.3664 4888.5954) (13242.9618 4899.4351)
      (13244.6718 4904.5344) (13248.7023 4907.2519) (13261.313 4917.8168) (13273.0229 4929.6183) (13283.4198 4942.0)
      (13295.7557 4925.2672) (13310.5954 4908.229) (13326.5802 4892.4885) (13343.3893 4878.2137) (13360.7176 4865.542)
      (13378.3053 4854.626) (13395.8168 4845.6031) (13412.9771 4838.6412) (13429.4809 4833.8626) (13426.229 4852.1374)
      (13421.0992 4871.1603) (13414.2137 4890.6107) (13405.6489 4910.1832) (13395.4809 4929.6031) (13383.8168 4948.5344)
      (13370.7328 4966.687) (13356.3206 4983.771) (13340.6718 4999.4809) (13323.8931 5013.4809) (13321.542 5015.0687)
      (13324.916 5027.6183) (13327.2977 5040.9618) (13328.2443 5053.4351) (13315.9542 5047.7099) (13303.4198 5040.5496)
      (13291.9389 5032.8092) (13287.2366 5035.2519) (13267.542 5042.3969) (13247.0534 5046.6412) (13229.4046 5033.7863)
      (13213.6183 5018.6412) (13199.6794 5001.5725) (13189.2519 4985.4962) (13173.7099 5007.4046) (13160.9924 5023.3893)
      (13164.1221 5029.313) (13172.7634 5048.8702) (13180.1985 5069.4809) (13186.2595 5090.8702) (13190.7939 5112.7939)
      (13193.6336 5134.9618) (13194.6412 5157.0992) (13193.6031 5178.9466) (13190.7176 5198.1374) (13194.1985 5195.374)
      (13205.6183 5180.2137) (13220.8244 5163.6489) (13237.542 5148.4275) (13255.4198 5134.6107) (13274.1679 5122.2901)
      (13293.4351 5111.5725) (13312.916 5102.5191) (13332.2748 5095.2366) (13351.2214 5089.8168) (13369.4046 5086.3206)
      (13386.5191 5084.8702) (13379.771 5102.1527) (13371.0382 5119.8168) (13360.4885 5137.542) (13348.2595 5155.0687)
      (13334.5038 5172.1221) (13319.3588 5188.4275) (13302.9924 5203.6794) (13285.5267 5217.6183) (13267.1145 5229.9695)
      (13247.9237 5240.4427) (13245.9389 5241.2672) (13248.7023 5243.1298) (13261.313 5253.6947) (13273.0229 5265.4962)
      (13283.7863 5278.3359) (13293.542 5291.9542) (13302.2137 5306.1069) (13309.7405 5320.5802) (13316.0763 5335.1298)
      (13321.1603 5349.5115) (13324.916 5363.4962) (13327.2977 5376.8397) (13328.2443 5389.313) (13315.9542 5383.5878)
      (13303.4198 5376.4275) (13290.8397 5367.9542) (13278.4122 5358.2595) (13272.1985 5352.7176) (13270.626 5354.7634)
      (13256.8244 5370.0916) (13241.4046 5384.9008) (13224.5802 5398.9466) (13206.5649 5411.9847) (13187.5267 5423.7557)
      (13167.6794 5434.0153) (13152.8244 5440.1985) (13160.3053 5443.2977) (13172.9466 5453.0076) (13182.6565 5465.6489)
      (13188.7634 5480.3817) (13190.8397 5496.1832) (13188.7634 5511.9847) (13182.6565 5526.7176) (13172.9466 5539.3588)
      (13160.3053 5549.0687) (13145.5725 5555.1756) (13135.771 5556.458) (13123.7405 5566.9924) (13107.2061 5579.3282)
      (13089.1908 5590.855) (13069.9542 5601.3435) (13049.7405 5610.6107) (13028.7634 5618.4427) (13007.2977 5624.6412)
      (12985.5725 5628.9924) (12963.8321 5631.3282) (12942.3053 5631.4046) (12921.2519 5629.0534) (12900.916 5624.0458)
      (12881.5267 5616.1985)
    ))
    ; P3143 -- see feature_dimensions_mm.csv
    ("06_ORNAMENT" 1 (
      (12885.4962 5923.6641) (12888.6107 5913.8626) (12897.4351 5905.1298) (12910.6107 5898.2901) (12926.0916 5893.6336)
      (12941.5725 5890.8702) (12954.9008 5889.1756) (12964.458 5887.313) (12969.4198 5883.9695) (12969.8321 5878.0153)
      (12966.6718 5868.8092) (12961.4809 5856.4122) (12956.1221 5841.6183) (12952.4122 5825.8779) (12951.7557 5811.0534)
      (12954.9008 5799.0382) (12961.8321 5791.4504) (12971.8779 5789.2366) (12983.8473 5792.5344) (12996.3664 5800.5191)
      (13008.1374 5811.5878) (13018.2595 5823.6183) (13026.4122 5834.3206) (13032.7939 5841.6641) (13038.1679 5844.2748)
      (13043.542 5841.6641) (13049.9237 5834.3206) (13058.0763 5823.6183) (13068.1985 5811.5878) (13079.9695 5800.5191)
      (13092.4885 5792.5344) (13104.458 5789.2366) (13114.5038 5791.4504) (13121.4351 5799.0382) (13124.5802 5811.0534)
      (13123.9237 5825.8779) (13120.2137 5841.6183) (13114.855 5856.4122) (13109.6641 5868.8092) (13106.5038 5878.0153)
      (13106.916 5883.9695) (13111.8779 5887.313) (13121.4351 5889.1756) (13134.7634 5890.8702) (13150.2443 5893.6336)
      (13165.7252 5898.2901) (13178.9008 5905.1298) (13187.7252 5913.8626) (13190.8397 5923.6641) (13187.7252 5933.4656)
      (13178.9008 5942.1985) (13165.7252 5949.0382) (13150.2443 5953.6947) (13134.7634 5956.458) (13121.4351 5958.1527)
      (13111.8779 5960.0153) (13106.916 5963.3588) (13106.5038 5969.313) (13109.6641 5978.5191) (13114.855 5990.916)
      (13120.2137 6005.7099) (13123.9237 6021.4351) (13124.5802 6036.2748) (13121.4351 6048.2901) (13114.5038 6055.8779)
      (13104.458 6058.0916) (13092.4885 6054.7939) (13079.9695 6046.8092) (13068.1985 6035.7405) (13058.0763 6023.7099)
      (13049.9237 6013.0076) (13043.542 6005.6641) (13038.1679 6003.0534) (13032.7939 6005.6641) (13026.4122 6013.0076)
      (13018.2595 6023.7099) (13008.1374 6035.7405) (12996.3664 6046.8092) (12983.8473 6054.7939) (12971.8779 6058.0916)
      (12961.8321 6055.8779) (12954.9008 6048.2901) (12951.7557 6036.2748) (12952.4122 6021.4351) (12956.1221 6005.7099)
      (12961.4809 5990.916) (12966.6718 5978.5191) (12969.8321 5969.313) (12969.4198 5963.3588) (12964.458 5960.0153)
      (12954.9008 5958.1527) (12941.5725 5956.458) (12926.0916 5953.6947) (12910.6107 5949.0382) (12897.4351 5942.1985)
      (12888.6107 5933.4656)
    ))
    ; P3144 -- see feature_dimensions_mm.csv
    ("06_ORNAMENT" 1 (
      (12900.7634 2137.4046) (12902.0 2133.4809) (12905.542 2130.0) (12910.8092 2127.2519) (12917.0076 2125.3893)
      (12923.1908 2124.2901) (12928.5344 2123.6031) (12932.3511 2122.8702) (12934.3359 2121.5267) (12934.5038 2119.145)
      (12933.2366 2115.4656) (12931.1603 2110.5038) (12929.0076 2104.5802) (12927.5267 2098.2901) (12927.2672 2092.3664)
      (12928.5191 2087.5573) (12931.2977 2084.5191) (12935.313 2083.6336) (12940.1069 2084.9466) (12945.1145 2088.1374)
      (12949.8168 2092.5802) (12953.8779 2097.3893) (12957.1298 2101.6641) (12959.6794 2104.6107) (12961.8321 2105.6489)
      (12963.9847 2104.6107) (12966.5344 2101.6641) (12969.7863 2097.3893) (12973.8473 2092.5802) (12978.5496 2088.1374)
      (12983.5573 2084.9466) (12988.3511 2083.6336) (12992.3664 2084.5191) (12995.145 2087.5573) (12996.3969 2092.3664)
      (12996.1374 2098.2901) (12994.6565 2104.5802) (12992.5038 2110.5038) (12990.4275 2115.4656) (12989.1603 2119.145)
      (12989.3282 2121.5267) (12991.313 2122.8702) (12995.1298 2123.6031) (13000.4733 2124.2901) (13006.6565 2125.3893)
      (13012.855 2127.2519) (13018.1221 2130.0) (13021.6641 2133.4809) (13022.9008 2137.4046) (13021.6641 2141.3282)
      (13018.1221 2144.8092) (13012.855 2147.5573) (13006.6565 2149.4198) (13000.4733 2150.5191) (12995.1298 2151.2061)
      (12991.313 2151.9389) (12989.3282 2153.2824) (12989.1603 2155.6641) (12990.4275 2159.3435) (12992.5038 2164.3053)
      (12994.6565 2170.229) (12995.6794 2174.5954) (12981.1145 2185.8473) (12979.2366 2187.0992) (12978.5496 2186.6718)
      (12973.8473 2182.229) (12969.7863 2177.4198) (12966.5344 2173.145) (12963.9847 2170.1985) (12961.8321 2169.1603)
      (12959.6794 2170.1985) (12957.1298 2173.145) (12953.8779 2177.4198) (12949.8168 2182.229) (12945.1145 2186.6718)
      (12940.1069 2189.8626) (12935.313 2191.1756) (12931.2977 2190.2901) (12928.5191 2187.2519) (12927.2672 2182.4427)
      (12927.5267 2176.5191) (12929.0076 2170.229) (12931.1603 2164.3053) (12933.2366 2159.3435) (12934.5038 2155.6641)
      (12934.3359 2153.2824) (12932.3511 2151.9389) (12928.5344 2151.2061) (12923.1908 2150.5191) (12917.0076 2149.4198)
      (12910.8092 2147.5573) (12905.542 2144.8092) (12902.0 2141.3282)
    ))
    ; P3145 -- see feature_dimensions_mm.csv
    ("06_ORNAMENT" 1 (
      (12900.7634 1374.0458) (12902.0 1370.1221) (12905.542 1366.6412) (12910.8092 1363.8931) (12917.0076 1362.0305)
      (12923.1908 1360.9313) (12928.5344 1360.2443) (12932.3511 1359.5115) (12934.3359 1358.1679) (12934.5038 1355.7863)
      (12933.2366 1352.1069) (12931.1603 1347.145) (12929.0076 1341.2214) (12927.5267 1334.9313) (12927.2672 1329.0076)
      (12928.5191 1324.1985) (12931.2977 1321.1603) (12935.313 1320.2748) (12940.1069 1321.5878) (12945.1145 1324.7786)
      (12949.8168 1329.2214) (12953.8779 1334.0305) (12957.1298 1338.3053) (12959.6794 1341.2519) (12961.8321 1342.2901)
      (12963.9847 1341.2519) (12966.5344 1338.3053) (12969.7863 1334.0305) (12973.8473 1329.2214) (12978.5496 1324.7786)
      (12983.5573 1321.5878) (12988.3511 1320.2748) (12992.3664 1321.1603) (12995.145 1324.1985) (12996.3969 1329.0076)
      (12996.1374 1334.9313) (12994.6565 1341.2214) (12992.5038 1347.145) (12990.4275 1352.1069) (12989.1603 1355.7863)
      (12989.3282 1358.1679) (12991.313 1359.5115) (12995.1298 1360.2443) (13000.4733 1360.9313) (13006.6565 1362.0305)
      (13012.855 1363.8931) (13018.1221 1366.6412) (13021.6641 1370.1221) (13022.9008 1374.0458) (13021.6641 1377.9695)
      (13018.1221 1381.4504) (13012.855 1384.1985) (13006.6565 1386.0611) (13000.4733 1387.1603) (12995.1298 1387.8473)
      (12991.313 1388.5802) (12989.3282 1389.9237) (12989.1603 1392.3053) (12990.4275 1395.9847) (12992.5038 1400.9466)
      (12994.6565 1406.8702) (12996.1374 1413.1603) (12996.1679 1413.9237) (12996.9924 1413.3435) (13007.2214 1407.4809)
      (13017.5878 1402.6565) (13027.9237 1398.916) (13038.0305 1396.3511) (13047.7405 1395.0076) (13045.771 1405.3435)
      (13042.7023 1415.9542) (13038.5802 1426.6718) (13033.4809 1437.313) (13027.4351 1447.7252) (13020.5038 1457.7252)
      (13012.7634 1467.1603) (13004.229 1475.8473) (12994.9771 1483.6183) (12985.0687 1490.3206) (12974.5344 1495.771)
      (12963.4351 1499.8015) (12951.8473 1502.2595) (12939.7863 1502.9618) (12940.9313 1490.458) (12943.8015 1478.458)
      (12948.1832 1467.0076) (12953.9389 1456.1679) (12960.8855 1446.0153) (12968.8244 1436.5954) (12977.6183 1427.9695)
      (12981.2214 1425.0076) (12978.5496 1423.313) (12973.8473 1418.8702) (12969.7863 1414.0611) (12966.5344 1409.7863)
      (12963.9847 1406.8397) (12961.8321 1405.8015) (12959.6794 1406.8397) (12957.1298 1409.7863) (12953.8779 1414.0611)
      (12949.8168 1418.8702) (12945.1145 1423.313) (12940.1069 1426.5038) (12935.313 1427.8168) (12931.2977 1426.9313)
      (12928.5191 1423.8931) (12927.2672 1419.084) (12927.5267 1413.1603) (12929.0076 1406.8702) (12931.1603 1400.9466)
      (12933.2366 1395.9847) (12934.5038 1392.3053) (12934.3359 1389.9237) (12932.3511 1388.5802) (12928.5344 1387.8473)
      (12923.1908 1387.1603) (12917.0076 1386.0611) (12910.8092 1384.1985) (12905.542 1381.4504) (12902.0 1377.9695)
    ))
    ; P3146 -- see feature_dimensions_mm.csv
    ("06_ORNAMENT" 1 (
      (12939.7863 1977.9542) (12952.2901 1979.0992) (12964.2901 1981.9695) (12975.7405 1986.3511) (12986.5802 1992.1069)
      (12996.7328 1999.0534) (13006.1527 2006.9924) (13014.7786 2015.7863) (13022.5496 2025.2214) (13029.4046 2035.1603)
      (13035.2672 2045.3893) (13040.0916 2055.7557) (13043.8321 2066.0916) (13046.3969 2076.1985) (13047.7405 2085.9084)
      (13037.4046 2083.9389) (13026.7939 2080.8702) (13016.0763 2076.7481) (13005.4351 2071.6489) (12995.0229 2065.6031)
      (12985.0229 2058.6718) (12975.5878 2050.9313) (12966.9008 2042.3969) (12959.1298 2033.145) (12952.4275 2023.2366)
      (12946.9771 2012.7023) (12942.9466 2001.6031) (12940.4885 1990.0153)
    ))
    ; P3147 -- see feature_dimensions_mm.csv
    ("06_ORNAMENT" 1 (
      (12992.3664 7374.0458) (13053.4351 7343.5115) (13114.5038 7374.0458) (13053.4351 7404.5802)
    ))
    ; P3148 -- see feature_dimensions_mm.csv
    ("06_ORNAMENT" 1 (
      (12992.3664 7282.4427) (13053.4351 7251.9084) (13114.5038 7282.4427) (13053.4351 7312.9771)
    ))
    ; P3149 -- see feature_dimensions_mm.csv
    ("06_ORNAMENT" 1 (
      (12992.3664 7190.8397) (13053.4351 7160.3053) (13114.5038 7190.8397) (13053.4351 7221.374)
    ))
    ; P3150 -- see feature_dimensions_mm.csv
    ("06_ORNAMENT" 1 (
      (12992.3664 5923.6641) (12994.6107 5909.5115) (13001.1145 5896.7481) (13011.2519 5886.6107) (13024.0153 5880.1069)
      (13038.1679 5877.8626) (13052.3206 5880.1069) (13065.084 5886.6107) (13075.2214 5896.7481) (13081.7252 5909.5115)
      (13083.9695 5923.6641) (13081.7252 5937.8168) (13075.2214 5950.5802) (13065.084 5960.7176) (13052.3206 5967.2214)
      (13038.1679 5969.4656) (13024.0153 5967.2214) (13011.2519 5960.7176) (13001.1145 5950.5802) (12994.6107 5937.8168)
    ))
    ; P3151 -- see feature_dimensions_mm.csv
    ("06_ORNAMENT" 1 (
      (13022.9008 3007.6336) (13053.4351 2977.0992) (13083.9695 3007.6336) (13053.4351 3038.1679)
    ))
    ; P3152 -- see feature_dimensions_mm.csv
    ("06_ORNAMENT" 1 (
      (13022.9008 2916.0305) (13053.4351 2885.4962) (13083.9695 2916.0305) (13053.4351 2946.5649)
    ))
    ; P3153 -- see feature_dimensions_mm.csv
    ("06_ORNAMENT" 1 (
      (13026.7176 1827.3893) (13038.1221 1822.1374) (13049.9389 1818.6107) (13062.0611 1816.687) (13074.3206 1816.2595)
      (13086.5802 1817.1908) (13098.7176 1819.3588) (13110.5802 1822.6565) (13122.0305 1826.9466) (13132.916 1832.1221)
      (13143.1298 1838.0458) (13152.4885 1844.6107) (13160.0763 1851.0076) (13159.3588 1871.5725) (13153.5115 1873.0076)
      (13142.1832 1874.7939) (13130.4122 1875.6947) (13118.3817 1875.6794) (13106.2443 1874.6718) (13094.2137 1872.6718)
      (13082.4275 1869.6336) (13071.0687 1865.5115) (13060.3053 1860.2748) (13050.3206 1853.8779) (13041.2824 1846.2901)
      (13033.3588 1837.4809)
    ))
    ; P3154 -- see feature_dimensions_mm.csv
    ("06_ORNAMENT" 1 (
      (13026.7176 1653.5267) (13033.9695 1643.2824) (13042.4427 1634.3053) (13051.9695 1626.5954) (13062.3664 1620.0916)
      (13073.4656 1614.7634) (13085.0534 1610.5802) (13096.9771 1607.4962) (13109.0382 1605.4962) (13121.0534 1604.5191)
      (13132.855 1604.5649) (13144.2595 1605.5573) (13155.0687 1607.4962) (13160.3053 1608.9618) (13160.3053 1628.7023)
      (13159.3435 1629.6336) (13150.4122 1636.855) (13140.6718 1643.5267) (13130.2443 1649.5115) (13119.2366 1654.7176)
      (13107.8168 1659.0076) (13096.0916 1662.2595) (13084.1832 1664.3664) (13072.2443 1665.2214) (13060.3969 1664.6718)
      (13048.7786 1662.626) (13037.5115 1658.9466)
    ))
    ; P3155 -- see feature_dimensions_mm.csv
    ("06_ORNAMENT" 1 (
      (13038.1679 5801.5267) (13042.8244 5778.8244) (13049.5878 5754.7023) (13058.3206 5729.5725) (13068.916 5703.8015)
      (13081.2672 5677.7863) (13095.2519 5651.9084) (13110.7481 5626.5649) (13127.6489 5602.1069) (13145.8321 5578.9618)
      (13165.1756 5557.4962) (13185.5725 5538.1069) (13206.9008 5521.1603) (13229.0534 5507.0534) (13251.9084 5496.1832)
      (13248.626 5522.6412) (13242.1679 5549.4198) (13235.0687 5569.8473) (13235.2519 5569.9542) (13248.7023 5579.0076)
      (13261.313 5589.5725) (13273.0229 5601.374) (13283.7863 5614.2137) (13293.542 5627.8321) (13302.2137 5641.9847)
      (13309.7405 5656.458) (13316.0763 5671.0076) (13321.1603 5685.3893) (13324.916 5699.374) (13327.2977 5712.7176)
      (13328.2443 5725.1908) (13315.9542 5719.4656) (13303.4198 5712.3053) (13290.8397 5703.8321) (13278.4122 5694.1374)
      (13266.3359 5683.3588) (13254.8092 5671.6183) (13244.0153 5659.0229) (13234.1832 5645.7099) (13225.4809 5631.7863)
      (13218.1374 5617.374) (13216.0763 5612.1374) (13206.9618 5629.145) (13193.2214 5651.2366) (13251.9084 5709.9237)
      (13175.5725 5786.2595) (13124.7023 5735.3893) (13115.9084 5744.2595) (13095.8626 5762.2595) (13076.0153 5777.9847)
      (13056.6565 5791.1603)
    ))
    ; P3156 -- see feature_dimensions_mm.csv
    ("06_ORNAMENT" 1 (
      (13038.1679 4793.8931) (13042.8244 4771.1908) (13049.5878 4747.0687) (13058.3206 4721.9389) (13068.916 4696.1679)
      (13081.2672 4670.1527) (13095.2519 4644.2748) (13110.7481 4618.9313) (13127.6489 4594.4733) (13145.8321 4571.3282)
      (13165.1756 4549.8626) (13185.5725 4530.4733) (13206.9008 4513.5267) (13229.0534 4499.4198) (13251.9084 4488.5496)
      (13248.626 4515.0076) (13242.1679 4541.7863) (13235.0687 4562.2137) (13235.2519 4562.3206) (13248.7023 4571.374)
      (13261.313 4581.9389) (13273.0229 4593.7405) (13283.7863 4606.5802) (13293.542 4620.1985) (13302.2137 4634.3511)
      (13309.7405 4648.8244) (13316.0763 4663.374) (13319.6489 4673.4962) (13330.3664 4657.7252) (13344.0611 4640.4427)
      (13358.5954 4624.6412) (13373.6947 4610.4885) (13389.1298 4598.229) (13404.5954 4588.0458) (13419.8473 4580.1527)
      (13420.2137 4598.7176) (13418.916 4618.3664) (13415.9389 4638.7786) (13411.3588 4659.6641) (13405.1756 4680.687)
      (13397.4198 4701.5267) (13388.1374 4721.8931) (13377.3435 4741.4504) (13365.0534 4759.9084) (13351.3282 4776.9313)
      (13336.1679 4792.1985) (13319.6183 4805.4198) (13301.6947 4816.2595) (13282.4427 4824.4275) (13262.626 4815.2672)
      (13244.1832 4803.4962) (13227.1756 4789.4656) (13211.6336 4773.5115) (13197.6031 4755.9389) (13185.0992 4737.0992)
      (13174.1679 4717.313) (13164.8702 4696.916) (13161.2519 4687.1756) (13155.1756 4694.8244) (13135.7863 4716.5954)
      (13115.9084 4736.626) (13095.8626 4754.626) (13076.0153 4770.3511) (13056.6565 4783.5267)
    ))
    ; P3157 -- see feature_dimensions_mm.csv
    ("06_ORNAMENT" 1 (
      (13038.1679 2839.6947) (13068.7023 2839.6947) (13053.4351 2854.9618)
    ))
    ; P3158 -- see feature_dimensions_mm.csv
    ("06_ORNAMENT" 1 (
      (13068.7023 4488.5496) (13070.7786 4472.7481) (13076.8855 4458.0153) (13086.5954 4445.374) (13099.2366 4435.6641)
      (13113.9695 4429.5573) (13129.771 4427.4809) (13145.5725 4429.5573) (13160.3053 4435.6641) (13172.9466 4445.374)
      (13182.6565 4458.0153) (13188.7634 4472.7481) (13190.8397 4488.5496) (13188.7634 4504.3511) (13182.6565 4519.084)
      (13172.9466 4531.7252) (13160.3053 4541.4351) (13145.5725 4547.542) (13129.771 4549.6183) (13113.9695 4547.542)
      (13099.2366 4541.4351) (13086.5954 4531.7252) (13076.8855 4519.084) (13070.7786 4504.3511)
    ))
    ; P3159 -- see feature_dimensions_mm.csv
    ("06_ORNAMENT" 1 (
      (13068.7023 4152.6718) (13070.7786 4136.8702) (13076.8855 4122.1374) (13086.5954 4109.4962) (13099.2366 4099.7863)
      (13113.9695 4093.6794) (13129.771 4091.6031) (13145.5725 4093.6794) (13160.3053 4099.7863) (13172.9466 4109.4962)
      (13182.6565 4122.1374) (13188.7634 4136.8702) (13190.8397 4152.6718) (13188.7634 4168.4733) (13182.6565 4183.2061)
      (13172.9466 4195.8473) (13160.3053 4205.5573) (13145.5725 4211.6641) (13129.771 4213.7405) (13113.9695 4211.6641)
      (13099.2366 4205.5573) (13086.5954 4195.8473) (13076.8855 4183.2061) (13070.7786 4168.4733)
    ))
    ; P3160 -- see feature_dimensions_mm.csv
    ("06_ORNAMENT" 1 (
      (13177.8779 5337.4198) (13196.1221 5331.542) (13216.9924 5326.4733) (13237.4046 5323.1145) (13243.6183 5322.5954)
      (13234.1832 5309.8321) (13225.4809 5295.9084) (13218.1374 5281.4962) (13216.0763 5276.2595) (13206.9618 5293.2672)
      (13191.0992 5318.7634)
    ))
    ; P3161 -- see feature_dimensions_mm.csv
    ("06_ORNAMENT" 1 (
      (13204.7634 4625.0534) (13208.5802 4628.687) (13223.3282 4644.9008) (13237.1298 4662.3511) (13249.6947 4680.855)
      (13260.8092 4700.2443) (13270.1985 4720.3206) (13277.6183 4740.8855) (13282.8092 4761.771) (13283.0076 4763.3282)
      (13283.6183 4759.0382) (13289.1908 4737.4656) (13296.916 4716.3511) (13302.6412 4704.1527) (13290.8397 4696.1985)
      (13278.4122 4686.5038) (13266.3359 4675.7252) (13254.8092 4663.9847) (13244.0153 4651.3893) (13234.1832 4638.0763)
      (13225.4809 4624.1527) (13218.1374 4609.7405) (13216.0763 4604.5038) (13206.9618 4621.5115)
    ))
    ; P3162 -- see feature_dimensions_mm.csv
    ("06_ORNAMENT" 1 (
      (13465.6489 7374.0458) (13526.7176 7343.5115) (13587.7863 7374.0458) (13526.7176 7404.5802)
    ))
    ; P3163 -- see feature_dimensions_mm.csv
    ("06_ORNAMENT" 1 (
      (13465.6489 7282.4427) (13526.7176 7251.9084) (13587.7863 7282.4427) (13526.7176 7312.9771)
    ))
    ; P3164 -- see feature_dimensions_mm.csv
    ("06_ORNAMENT" 1 (
      (13465.6489 7190.8397) (13526.7176 7160.3053) (13587.7863 7190.8397) (13526.7176 7221.374)
    ))
    ; P3165 -- see feature_dimensions_mm.csv
    ("07_RAILINGS" 0 (
      (961.8321 5816.7939) (1038.1679 5816.7939)
    ))
    ; P3166 -- see feature_dimensions_mm.csv
    ("07_RAILINGS" 0 (
      (961.8321 5465.6489) (1038.1679 5465.6489)
    ))
    ; P3167 -- see feature_dimensions_mm.csv
    ("07_RAILINGS" 0 (
      (1038.1679 5816.7939) (1058.0153 5816.7939)
    ))
    ; P3168 -- see feature_dimensions_mm.csv
    ("07_RAILINGS" 0 (
      (1038.1679 5465.6489) (1038.1679 5816.7939)
    ))
    ; P3169 -- see feature_dimensions_mm.csv
    ("07_RAILINGS" 0 (
      (1038.1679 5465.6489) (1058.0153 5465.6489)
    ))
    ; P3170 -- see feature_dimensions_mm.csv
    ("07_RAILINGS" 0 (
      (1058.0153 5816.7939) (1129.771 5816.7939)
    ))
    ; P3171 -- see feature_dimensions_mm.csv
    ("07_RAILINGS" 0 (
      (1058.0153 5816.7939) (1058.0153 5465.6489)
    ))
    ; P3172 -- see feature_dimensions_mm.csv
    ("07_RAILINGS" 0 (
      (1058.0153 5465.6489) (1129.771 5465.6489)
    ))
    ; P3173 -- see feature_dimensions_mm.csv
    ("07_RAILINGS" 0 (
      (1129.771 5816.7939) (1149.6183 5816.7939)
    ))
    ; P3174 -- see feature_dimensions_mm.csv
    ("07_RAILINGS" 0 (
      (1129.771 5465.6489) (1129.771 5816.7939)
    ))
    ; P3175 -- see feature_dimensions_mm.csv
    ("07_RAILINGS" 0 (
      (1129.771 5465.6489) (1149.6183 5465.6489)
    ))
    ; P3176 -- see feature_dimensions_mm.csv
    ("07_RAILINGS" 0 (
      (1149.6183 5816.7939) (1221.374 5816.7939)
    ))
    ; P3177 -- see feature_dimensions_mm.csv
    ("07_RAILINGS" 0 (
      (1149.6183 5816.7939) (1149.6183 5465.6489)
    ))
    ; P3178 -- see feature_dimensions_mm.csv
    ("07_RAILINGS" 0 (
      (1149.6183 5465.6489) (1221.374 5465.6489)
    ))
    ; P3179 -- see feature_dimensions_mm.csv
    ("07_RAILINGS" 0 (
      (1221.374 5816.7939) (1241.2214 5816.7939)
    ))
    ; P3180 -- see feature_dimensions_mm.csv
    ("07_RAILINGS" 0 (
      (1221.374 5465.6489) (1221.374 5816.7939)
    ))
    ; P3181 -- see feature_dimensions_mm.csv
    ("07_RAILINGS" 0 (
      (1221.374 5465.6489) (1241.2214 5465.6489)
    ))
    ; P3182 -- see feature_dimensions_mm.csv
    ("07_RAILINGS" 0 (
      (1241.2214 5816.7939) (1312.9771 5816.7939)
    ))
    ; P3183 -- see feature_dimensions_mm.csv
    ("07_RAILINGS" 0 (
      (1241.2214 5816.7939) (1241.2214 5465.6489)
    ))
    ; P3184 -- see feature_dimensions_mm.csv
    ("07_RAILINGS" 0 (
      (1241.2214 5465.6489) (1312.9771 5465.6489)
    ))
    ; P3185 -- see feature_dimensions_mm.csv
    ("07_RAILINGS" 0 (
      (1312.9771 5816.7939) (1332.8244 5816.7939)
    ))
    ; P3186 -- see feature_dimensions_mm.csv
    ("07_RAILINGS" 0 (
      (1312.9771 5465.6489) (1312.9771 5816.7939)
    ))
    ; P3187 -- see feature_dimensions_mm.csv
    ("07_RAILINGS" 0 (
      (1312.9771 5465.6489) (1332.8244 5465.6489)
    ))
    ; P3188 -- see feature_dimensions_mm.csv
    ("07_RAILINGS" 0 (
      (1332.8244 5816.7939) (1358.7786 5816.7939)
    ))
    ; P3189 -- see feature_dimensions_mm.csv
    ("07_RAILINGS" 0 (
      (1332.8244 5816.7939) (1332.8244 5465.6489)
    ))
    ; P3190 -- see feature_dimensions_mm.csv
    ("07_RAILINGS" 0 (
      (1332.8244 5465.6489) (1358.7786 5465.6489)
    ))
    ; P3191 -- see feature_dimensions_mm.csv
    ("07_RAILINGS" 0 (
      (1969.4656 3633.5878) (1969.4656 3679.3893) (1969.4656 4473.2824) (2045.8015 4473.2824)
    ))
    ; P3192 -- see feature_dimensions_mm.csv
    ("07_RAILINGS" 0 (
      (2229.0076 4427.4809) (2259.542 4427.4809)
    ))
    ; P3193 -- see feature_dimensions_mm.csv
    ("07_RAILINGS" 0 (
      (2229.0076 3832.0611) (2229.0076 4412.2137) (2229.0076 4427.4809)
    ))
    ; P3194 -- see feature_dimensions_mm.csv
    ("07_RAILINGS" 0 (
      (2229.0076 4427.4809) (2030.5344 4427.4809) (2030.5344 4412.2137) (2030.5344 3832.0611) (2045.8015 3832.0611)
      (2152.6718 3832.0611) (2229.0076 3832.0611)
    ))
    ; P3195 -- see feature_dimensions_mm.csv
    ("07_RAILINGS" 0 (
      (2229.0076 3832.0611) (2259.542 3832.0611)
    ))
    ; P3196 -- see feature_dimensions_mm.csv
    ("07_RAILINGS" 0 (
      (2259.542 4427.4809) (2961.8321 4427.4809)
    ))
    ; P3197 -- see feature_dimensions_mm.csv
    ("07_RAILINGS" 0 (
      (2259.542 4427.4809) (2259.542 4412.2137) (2259.542 3832.0611)
    ))
    ; P3198 -- see feature_dimensions_mm.csv
    ("07_RAILINGS" 0 (
      (2259.542 3832.0611) (2414.8244 3832.0611) (2415.7099 3832.0611) (2570.5496 3832.0611) (2571.4351 3832.0611)
      (2726.2748 3832.0611) (2727.1603 3832.0611) (2882.0 3832.0611)
    ))
    ; P3199 -- see feature_dimensions_mm.csv
    ("07_RAILINGS" 0 (
      (2882.8855 3832.0611) (2938.9313 3832.0611) (2961.8321 3832.0611)
    ))
    ; P3200 -- see feature_dimensions_mm.csv
    ("07_RAILINGS" 0 (
      (2961.8321 4427.4809) (2992.3664 4427.4809)
    ))
    ; P3201 -- see feature_dimensions_mm.csv
    ("07_RAILINGS" 0 (
      (2961.8321 3832.0611) (2961.8321 4412.2137) (2961.8321 4427.4809)
    ))
    ; P3202 -- see feature_dimensions_mm.csv
    ("07_RAILINGS" 0 (
      (2961.8321 3832.0611) (2992.3664 3832.0611) (3015.2672 3832.0611) (3037.7252 3832.0611) (3038.6107 3832.0611)
      (3193.4504 3832.0611) (3194.3359 3832.0611) (3349.1756 3832.0611) (3350.0611 3832.0611) (3504.9008 3832.0611)
      (3505.7863 3832.0611) (3660.626 3832.0611)
    ))
    ; P3203 -- see feature_dimensions_mm.csv
    ("07_RAILINGS" 0 (
      (2992.3664 4427.4809) (3725.1908 4427.4809)
    ))
    ; P3204 -- see feature_dimensions_mm.csv
    ("07_RAILINGS" 0 (
      (2992.3664 4427.4809) (2992.3664 4412.2137)
    ))
    ; P3205 -- see feature_dimensions_mm.csv
    ("07_RAILINGS" 0 (
      (3725.1908 4427.4809) (3755.7252 4427.4809)
    ))
    ; P3206 -- see feature_dimensions_mm.csv
    ("07_RAILINGS" 0 (
      (3755.7252 4427.4809) (3755.7252 4412.2137) (3755.7252 3832.0611) (3725.1908 3832.0611) (3725.1908 4412.2137)
      (3725.1908 4427.4809)
    ))
    ; P3207 -- see feature_dimensions_mm.csv
    ("07_RAILINGS" 0 (
      (3755.7252 4427.4809) (3923.6641 4427.4809) (3923.6641 4412.2137)
    ))
    ; P3208 -- see feature_dimensions_mm.csv
    ("07_RAILINGS" 0 (
      (3908.3969 4473.2824) (3984.7328 4473.2824)
    ))
    ; P3209 -- see feature_dimensions_mm.csv
    ("07_RAILINGS" 0 (
      (4595.4198 5816.7939) (4671.7557 5816.7939)
    ))
    ; P3210 -- see feature_dimensions_mm.csv
    ("07_RAILINGS" 0 (
      (4671.7557 5816.7939) (4691.6031 5816.7939)
    ))
    ; P3211 -- see feature_dimensions_mm.csv
    ("07_RAILINGS" 0 (
      (4691.6031 5816.7939) (4691.6031 5465.6489) (4671.7557 5465.6489) (4671.7557 5816.7939)
    ))
    ; P3212 -- see feature_dimensions_mm.csv
    ("07_RAILINGS" 0 (
      (4691.6031 5816.7939) (4763.3588 5816.7939)
    ))
    ; P3213 -- see feature_dimensions_mm.csv
    ("07_RAILINGS" 0 (
      (4763.3588 5816.7939) (4783.2061 5816.7939)
    ))
    ; P3214 -- see feature_dimensions_mm.csv
    ("07_RAILINGS" 0 (
      (4783.2061 5816.7939) (4783.2061 5465.6489) (4763.3588 5465.6489) (4763.3588 5816.7939)
    ))
    ; P3215 -- see feature_dimensions_mm.csv
    ("07_RAILINGS" 0 (
      (4783.2061 5816.7939) (4854.9618 5816.7939)
    ))
    ; P3216 -- see feature_dimensions_mm.csv
    ("07_RAILINGS" 0 (
      (4854.9618 5816.7939) (4874.8092 5816.7939)
    ))
    ; P3217 -- see feature_dimensions_mm.csv
    ("07_RAILINGS" 0 (
      (4854.9618 5465.6489) (4854.9618 5816.7939)
    ))
    ; P3218 -- see feature_dimensions_mm.csv
    ("07_RAILINGS" 0 (
      (4874.8092 5816.7939) (4946.5649 5816.7939)
    ))
    ; P3219 -- see feature_dimensions_mm.csv
    ("07_RAILINGS" 0 (
      (4874.8092 5816.7939) (4874.8092 5465.6489)
    ))
    ; P3220 -- see feature_dimensions_mm.csv
    ("07_RAILINGS" 0 (
      (4946.5649 5816.7939) (4966.4122 5816.7939)
    ))
    ; P3221 -- see feature_dimensions_mm.csv
    ("07_RAILINGS" 0 (
      (4946.5649 5465.6489) (4946.5649 5816.7939)
    ))
    ; P3222 -- see feature_dimensions_mm.csv
    ("07_RAILINGS" 0 (
      (4966.4122 5816.7939) (4992.3664 5816.7939)
    ))
    ; P3223 -- see feature_dimensions_mm.csv
    ("07_RAILINGS" 0 (
      (4966.4122 5816.7939) (4966.4122 5465.6489)
    ))
    ; P3224 -- see feature_dimensions_mm.csv
    ("07_RAILINGS" 0 (
      (8778.626 3832.0611) (8778.626 4412.2137)
    ))
    ; P3225 -- see feature_dimensions_mm.csv
    ("07_RAILINGS" 0 (
      (9450.3817 4316.0305) (9450.3817 4328.0153) (9450.3817 4360.6412) (9450.3817 4412.2137)
    ))
    ; P3226 -- see feature_dimensions_mm.csv
    ("07_RAILINGS" 0 (
      (9450.3817 3970.5802) (9450.3817 3992.8855) (9450.3817 4025.9542) (9450.3817 4037.9389) (9450.3817 4070.5649)
      (9450.3817 4227.5878)
    ))
    ; P3227 -- see feature_dimensions_mm.csv
    ("07_RAILINGS" 0 (
      (9450.3817 3832.0611) (9450.3817 3937.5115)
    ))
    ; P3228 -- see feature_dimensions_mm.csv
    ("07_RAILINGS" 0 (
      (9473.2824 4412.2137) (9496.1832 4412.2137)
    ))
    ; P3229 -- see feature_dimensions_mm.csv
    ("07_RAILINGS" 0 (
      (9496.1832 3832.0611) (9473.2824 3832.0611)
    ))
    ; P3230 -- see feature_dimensions_mm.csv
    ("07_RAILINGS" 0 (
      (10198.4733 3832.0611) (10198.4733 4412.2137) (10183.2061 4412.2137) (10091.6031 4412.2137) (10030.5344 4412.2137)
      (10004.5802 4412.2137) (9972.7786 4412.2137) (9950.8855 4412.2137) (9919.084 4412.2137) (9859.542 4412.2137)
      (9827.7405 4412.2137) (9805.8473 4412.2137) (9774.0458 4412.2137) (9714.5038 4412.2137) (9682.7023 4412.2137)
      (9660.8092 4412.2137) (9629.0076 4412.2137) (9569.4656 4412.2137) (9537.6641 4412.2137) (9526.7176 4412.2137)
      (9511.4504 4412.2137) (9503.8168 4412.2137) (9496.1832 4412.2137)
    ))
    ; P3231 -- see feature_dimensions_mm.csv
    ("07_RAILINGS" 0 (
      (9496.1832 4412.2137) (9496.1832 3832.0611)
    ))
    ; P3232 -- see feature_dimensions_mm.csv
    ("07_RAILINGS" 0 (
      (9503.8168 3832.0611) (9496.1832 3832.0611)
    ))
    ; P3233 -- see feature_dimensions_mm.csv
    ("07_RAILINGS" 0 (
      (9714.5038 3832.0611) (9774.0458 3832.0611)
    ))
    ; P3234 -- see feature_dimensions_mm.csv
    ("07_RAILINGS" 0 (
      (10274.8092 3618.3206) (10274.8092 3633.5878) (10290.0763 3633.5878) (10290.0763 3664.1221) (10290.0763 3740.458)
      (10290.0763 4473.2824)
    ))
    ; P3235 -- see feature_dimensions_mm.csv
    ("07_RAILINGS" 0 (
      (10290.0763 5816.7939) (10366.4122 5816.7939)
    ))
    ; P3236 -- see feature_dimensions_mm.csv
    ("07_RAILINGS" 0 (
      (10366.4122 5816.7939) (10386.2595 5816.7939)
    ))
    ; P3237 -- see feature_dimensions_mm.csv
    ("07_RAILINGS" 0 (
      (10366.4122 5465.6489) (10366.4122 5816.7939)
    ))
    ; P3238 -- see feature_dimensions_mm.csv
    ("07_RAILINGS" 0 (
      (10386.2595 5816.7939) (10458.0153 5816.7939)
    ))
    ; P3239 -- see feature_dimensions_mm.csv
    ("07_RAILINGS" 0 (
      (10386.2595 5816.7939) (10386.2595 5465.6489)
    ))
    ; P3240 -- see feature_dimensions_mm.csv
    ("07_RAILINGS" 0 (
      (10458.0153 5816.7939) (10477.8626 5816.7939)
    ))
    ; P3241 -- see feature_dimensions_mm.csv
    ("07_RAILINGS" 0 (
      (10458.0153 5465.6489) (10458.0153 5816.7939)
    ))
    ; P3242 -- see feature_dimensions_mm.csv
    ("07_RAILINGS" 0 (
      (10477.8626 5816.7939) (10549.6183 5816.7939)
    ))
    ; P3243 -- see feature_dimensions_mm.csv
    ("07_RAILINGS" 0 (
      (10477.8626 5816.7939) (10477.8626 5465.6489)
    ))
    ; P3244 -- see feature_dimensions_mm.csv
    ("07_RAILINGS" 0 (
      (10549.6183 5816.7939) (10569.4656 5816.7939)
    ))
    ; P3245 -- see feature_dimensions_mm.csv
    ("07_RAILINGS" 0 (
      (10549.6183 5465.6489) (10549.6183 5816.7939)
    ))
    ; P3246 -- see feature_dimensions_mm.csv
    ("07_RAILINGS" 0 (
      (10569.4656 5816.7939) (10641.2214 5816.7939)
    ))
    ; P3247 -- see feature_dimensions_mm.csv
    ("07_RAILINGS" 0 (
      (10569.4656 5816.7939) (10569.4656 5465.6489)
    ))
    ; P3248 -- see feature_dimensions_mm.csv
    ("07_RAILINGS" 0 (
      (10641.2214 5816.7939) (10661.0687 5816.7939)
    ))
    ; P3249 -- see feature_dimensions_mm.csv
    ("07_RAILINGS" 0 (
      (10641.2214 5465.6489) (10641.2214 5816.7939)
    ))
    ; P3250 -- see feature_dimensions_mm.csv
    ("07_RAILINGS" 0 (
      (10661.0687 5816.7939) (10687.0229 5816.7939)
    ))
    ; P3251 -- see feature_dimensions_mm.csv
    ("07_RAILINGS" 0 (
      (10661.0687 5816.7939) (10661.0687 5465.6489)
    ))
    ; P3252 -- see feature_dimensions_mm.csv
    ("07_RAILINGS" 0 (
      (13068.7023 3633.5878) (11053.4351 3633.5878)
    ))
    ; P3253 -- see feature_dimensions_mm.csv
    ("07_RAILINGS" 0 (
      (11114.5038 4412.2137) (11114.5038 4427.4809) (11312.9771 4427.4809)
    ))
    ; P3254 -- see feature_dimensions_mm.csv
    ("07_RAILINGS" 0 (
      (11312.9771 4427.4809) (11343.5115 4427.4809)
    ))
    ; P3255 -- see feature_dimensions_mm.csv
    ("07_RAILINGS" 0 (
      (11343.5115 4427.4809) (11343.5115 4412.2137) (11343.5115 3832.0611) (11312.9771 3832.0611) (11312.9771 4412.2137)
      (11312.9771 4427.4809)
    ))
    ; P3256 -- see feature_dimensions_mm.csv
    ("07_RAILINGS" 0 (
      (11343.5115 4427.4809) (12045.8015 4427.4809)
    ))
    ; P3257 -- see feature_dimensions_mm.csv
    ("07_RAILINGS" 0 (
      (12045.8015 4427.4809) (12076.3359 4427.4809)
    ))
    ; P3258 -- see feature_dimensions_mm.csv
    ("07_RAILINGS" 0 (
      (12045.8015 4412.2137) (12045.8015 4427.4809)
    ))
    ; P3259 -- see feature_dimensions_mm.csv
    ("07_RAILINGS" 0 (
      (12076.3359 3832.0611) (12045.8015 3832.0611)
    ))
    ; P3260 -- see feature_dimensions_mm.csv
    ("07_RAILINGS" 0 (
      (12076.3359 4427.4809) (12809.1603 4427.4809)
    ))
    ; P3261 -- see feature_dimensions_mm.csv
    ("07_RAILINGS" 0 (
      (12076.3359 4427.4809) (12076.3359 4412.2137)
    ))
    ; P3262 -- see feature_dimensions_mm.csv
    ("07_RAILINGS" 0 (
      (12589.7557 3832.0611) (12744.5954 3832.0611)
    ))
    ; P3263 -- see feature_dimensions_mm.csv
    ("07_RAILINGS" 0 (
      (12745.4809 3832.0611) (12778.626 3832.0611) (12809.1603 3832.0611)
    ))
    ; P3264 -- see feature_dimensions_mm.csv
    ("07_RAILINGS" 0 (
      (12809.1603 4427.4809) (12839.6947 4427.4809)
    ))
    ; P3265 -- see feature_dimensions_mm.csv
    ("07_RAILINGS" 0 (
      (12809.1603 3832.0611) (12809.1603 4412.2137) (12809.1603 4427.4809)
    ))
    ; P3266 -- see feature_dimensions_mm.csv
    ("07_RAILINGS" 0 (
      (12809.1603 3832.0611) (12839.6947 3832.0611)
    ))
    ; P3267 -- see feature_dimensions_mm.csv
    ("07_RAILINGS" 0 (
      (12839.6947 4427.4809) (13007.6336 4427.4809) (13007.6336 4412.2137)
    ))
    ; P3268 -- see feature_dimensions_mm.csv
    ("07_RAILINGS" 0 (
      (12839.6947 4427.4809) (12839.6947 4412.2137) (12839.6947 3832.0611)
    ))
    ; P3269 -- see feature_dimensions_mm.csv
    ("07_RAILINGS" 0 (
      (12839.6947 3832.0611) (12885.4962 3832.0611) (12992.3664 3832.0611)
    ))
    ; P3270 -- see feature_dimensions_mm.csv
    ("07_RAILINGS" 0 (
      (13068.7023 4439.4504) (13068.7023 4360.8244) (13068.7023 4152.6718) (13068.7023 4103.5725)
    ))
    ; P3271 -- see feature_dimensions_mm.csv
    ("08_STEPS" 0 (
      (10595.4198 122.1374) (8335.8779 122.1374)
    ))
    ; P3272 -- see feature_dimensions_mm.csv
    ("08_STEPS" 0 (
      (10595.4198 122.1374) (10778.626 122.1374) (10778.626 15.2672) (8152.6718 15.2672) (8152.6718 122.1374)
      (8335.8779 122.1374)
    ))
    ; P3273 -- see feature_dimensions_mm.csv
    ("08_STEPS" 0 (
      (8335.8779 122.1374) (8335.8779 213.7405) (8519.084 213.7405)
    ))
    ; P3274 -- see feature_dimensions_mm.csv
    ("08_STEPS" 0 (
      (10412.2137 213.7405) (8519.084 213.7405)
    ))
    ; P3275 -- see feature_dimensions_mm.csv
    ("08_STEPS" 0 (
      (8519.084 213.7405) (8519.084 290.0763) (8519.084 305.3435) (8702.2901 305.3435)
    ))
    ; P3276 -- see feature_dimensions_mm.csv
    ("08_STEPS" 0 (
      (10229.0076 305.3435) (8702.2901 305.3435)
    ))
    ; P3277 -- see feature_dimensions_mm.csv
    ("08_STEPS" 0 (
      (8702.2901 305.3435) (8702.2901 320.6107) (8702.2901 396.9466) (8748.0916 396.9466) (8839.6947 396.9466)
      (8916.0305 396.9466) (10076.3359 396.9466) (10152.6718 396.9466) (10229.0076 396.9466) (10229.0076 320.6107)
      (10229.0076 305.3435)
    ))
    ; P3278 -- see feature_dimensions_mm.csv
    ("08_STEPS" 0 (
      (10229.0076 305.3435) (10412.2137 305.3435) (10412.2137 290.0763) (10412.2137 213.7405)
    ))
    ; P3279 -- see feature_dimensions_mm.csv
    ("08_STEPS" 0 (
      (10412.2137 213.7405) (10595.4198 213.7405) (10595.4198 122.1374)
    ))
    ; P3280 -- see feature_dimensions_mm.csv
    ("08_STEPS" 1 (
      (-381.6794 0.0) (14702.2901 0.0) (14702.2901 -15.2672) (-381.6794 -15.2672)
    ))
    ; P3281 -- see feature_dimensions_mm.csv
    ("08_STEPS" 1 (
      (2564.8855 137.4046) (4824.4275 137.4046) (4824.4275 45.8015) (2564.8855 45.8015)
    ))
    ; P3282 -- see feature_dimensions_mm.csv
    ("08_STEPS" 1 (
      (2793.8931 244.2748) (4610.687 244.2748) (4610.687 152.6718) (2793.8931 152.6718)
    ))
    ; P3283 -- see feature_dimensions_mm.csv
    ("08_STEPS" 1 (
      (3007.6336 335.8779) (4396.9466 335.8779) (4396.9466 259.542) (3007.6336 259.542)
    ))
    ; P3284 -- see feature_dimensions_mm.csv
    ("08_STEPS" 1 (
      (3221.374 442.7481) (4152.6718 442.7481) (4167.9389 442.7481) (4167.9389 351.145) (3221.374 351.145)
    ))
  ))
(princ "\nClean facade loaded. Type PALACE to draw, or PALACEINFO for help.")
(princ)

(setq PALC:SIZES '(
  ("OVERALL_WIDTH" 14000 nil)
  ("TOWER_HEIGHT" nil 10611)
  ("MIDDLE_CROWN" nil 8641)
  ("SIDE_CROWNS" nil 8076)
  ("BELT_CORNICE" nil 3298)
  ("LEFT_DOOR" 931 2046)
  ("CENTRAL_DOOR" 947 1939)
  ("LEFT_BALCONY" 1863 2000)
  ("RIGHT_BALCONY" 1863 2000)
  ("RECESS_OPENING" 1389 1893)
  ("NARROW_TALL_WINDOWS" 901 4748)
  ("MIDDLE_TALL_WINDOW" 1221 4748)
  ("GROUND_ROSE_WINDOWS" 1221 1786)
  ("LEFT_WING" 4031 nil)
  ("RIGHT_WING" 3542 nil)
  ("CENTRAL_BAY" 3679 nil)
))
