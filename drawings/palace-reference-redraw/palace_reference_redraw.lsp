; palace_reference_redraw.lsp -- self-contained clean facade reconstruction
; Units: millimetres. Nominal facade width: 14000 (ESTIMATED, NOT SURVEYED).
; AutoCAD for Windows with Visual LISP/ActiveX. Load with APPLOAD; run PALACE.
; Shared edges occur once. Closed contours may contain connected junction-to-junction chains.
; All visible facade entities: RGB black, physical lineweight 0.18 mm.
; No external DXF, image, Python, network, or package is required to draw this data.
; Native dimension creation uses AutoCAD ActiveX; this environment could not execute AutoCAD.
(vl-load-com)

(defun PALC:emit (data)
  (if (null (entmake data))
    (progn (princ "\nPALACE: AutoCAD rejected an entity; undo this operation if necessary.") (quit))))

(defun PALC:layer (name white / full)
  (setq full (strcat "PALC_" name))
  (if (null (tblsearch "LAYER" full))
    (PALC:emit
      (list '(0 . "LAYER") '(100 . "AcDbSymbolTableRecord")
            '(100 . "AcDbLayerTableRecord") (cons 2 full) '(70 . 0)
            '(62 . 7) '(6 . "Continuous") '(370 . 18)
            (cons 420 (if white 16777215 0)))))
  full)

(defun PALC:poly (row / pts)
  (setq pts (caddr row))
  (PALC:emit
    (append
      (list '(0 . "LWPOLYLINE") '(100 . "AcDbEntity")
            (cons 8 (strcat "PALC_" (car row))) '(62 . 7) '(420 . 0) '(370 . 18) '(6 . "Continuous")
            '(100 . "AcDbPolyline") (cons 90 (length pts)) (cons 70 (cadr row))
            '(38 . 0.0) '(43 . 0.0))
      (mapcar '(lambda (p) (cons 10 p)) pts))))

(defun PALC:build (name / row)
  (PALC:emit
    (list '(0 . "BLOCK") '(100 . "AcDbEntity") '(8 . "0")
          '(100 . "AcDbBlockBegin") (cons 2 name) '(70 . 0) '(10 0.0 0.0 0.0) (cons 3 name) '(1 . "")))
  (PALC:emit
    (list '(0 . "SOLID") '(100 . "AcDbEntity") '(8 . "PALC_00_WHITE_BACKGROUND")
          '(62 . 7) '(420 . 16777215) '(370 . 18) '(100 . "AcDbTrace")
          '(10 -2412.2137 -1175.5725 0.0) '(11 16213.7405 -1175.5725 0.0)
          '(12 -2412.2137 12015.2672 0.0) '(13 16213.7405 12015.2672 0.0)))
  (foreach row PALC:DATA (PALC:poly row))
  (PALC:emit
    '((0 . "TEXT") (100 . "AcDbEntity") (8 . "PALC_10_REFERENCE_TITLE")
      (62 . 7) (420 . 0) (370 . 18) (100 . "AcDbText")
      (10 6900.7634 -793.8931 0.0) (40 . 366.4122)
      (1 . "Modern Islamic Commercial Elevation") (50 . 0.0) (41 . 1.0)
      (7 . "PALC_REFERENCE_ARIAL") (72 . 1) (11 6900.7634 -793.8931 0.0)
      (100 . "AcDbText") (73 . 0)))
  (PALC:emit '((0 . "ENDBLK") (100 . "AcDbEntity") (8 . "0") (100 . "AcDbBlockEnd"))))

(defun PALC:point (xy base factor)
  (list (+ (car base) (* factor (car xy)))
        (+ (cadr base) (* factor (cadr xy))) (caddr base)))

(defun PALC:property (obj name value)
  (if (vlax-property-available-p obj name T)
    (vlax-put-property obj name value)))

(defun PALC:dimension (space row base factor / obj colour item)
  (setq obj
    (vla-AddDimRotated space
      (vlax-3d-point (PALC:point (nth 0 row) base factor))
      (vlax-3d-point (PALC:point (nth 1 row) base factor))
      (vlax-3d-point (PALC:point (nth 2 row) base factor))
      (nth 3 row)))
  (vla-put-Layer obj "PALC_09_ESTIMATED_DIMS")
  (vla-put-Lineweight obj 18)
  (setq colour (vla-get-TrueColor obj))
  (vla-SetRGB colour 0 0 0)
  (vla-put-TrueColor obj colour)
  (vlax-release-object colour)
  (foreach item
    (list (cons 'TextHeight (* factor 145.0))
          (cons 'ArrowheadSize (* factor 100.0))
          (cons 'ExtensionLineOffset (* factor 75.0))
          (cons 'ExtensionLineExtend (* factor 65.0))
          (cons 'DimensionLineWeight 18) (cons 'ExtensionLineWeight 18)
          (cons 'DimensionLineColor 0) (cons 'ExtensionLineColor 0) (cons 'TextColor 0)
          (cons 'PrimaryUnitsPrecision 0) (cons 'LinearScaleFactor 1.0) (cons 'ScaleFactor 1.0)
          (cons 'Arrowhead1Type 0) (cons 'Arrowhead2Type 0)
          (cons 'DimLine1Suppress 0) (cons 'DimLine2Suppress 0)
          (cons 'ExtLine1Suppress 0) (cons 'ExtLine2Suppress 0)
          (cons 'DimensionLinetype "Continuous") (cons 'ExtLine1Linetype "Continuous") (cons 'ExtLine2Linetype "Continuous")
          (cons 'UnitsFormat 2) (cons 'TextOverride "<> mm (est.)"))
    (PALC:property obj (car item) (cdr item)))
  (vla-Update obj)
  (vlax-vla-object->ename obj))

(defun PALC:dimensions (record / acad doc space row old result base factor)
  (setq acad (vlax-get-acad-object) doc (vla-get-ActiveDocument acad)
        space (vla-get-ModelSpace doc) base (cadr record) factor (caddr record))
  ; Re-running PALACEDIMS replaces only dimensions tracked for this last insertion.
  (foreach old (cadddr record) (if (entget old) (entdel old)))
  (setq result nil)
  (foreach row PALC:DIMS
    (setq result (cons (PALC:dimension space row base factor) result)))
  (list (car record) base factor (reverse result)))

(defun c:PALACE (/ *error* acad doc mark base factor width name count entity oldlast dims row)
  (setq acad (vlax-get-acad-object) doc (vla-get-ActiveDocument acad)
        oldlast PALC:LAST mark nil entity nil)
  (defun *error* (message)
    (if mark (vl-catch-all-apply 'vla-EndUndoMark (list doc)))
    (setq PALC:LAST oldlast)
    (if (not (wcmatch (strcase message) "*CANCEL*,*QUIT*,*BREAK*"))
      (princ (strcat "\nPALACE error: " message)))
    (princ "\nIf an operation was interrupted, UNDO once removes its new drawing objects.")
    (princ))
  (princ "\nPALACE: estimated geometry in mm. Recommended: use a new blank drawing.")
  (setq base (getpoint "\nPick the ground-datum insertion point: "))
  (if base
    (progn
      (setq base (trans base 1 0))
      (initget 6)
      (setq width (getdist "\nEstimated overall facade width in mm <14000>: "))
      (if (null width) (setq width 14000.0))
      (setq factor (/ width 14000.0))
      (vla-StartUndoMark doc) (setq mark T)
      (PALC:layer "00_WHITE_BACKGROUND" T)
      (foreach row PALC:LAYERS (PALC:layer row nil))
      (PALC:layer "09_ESTIMATED_DIMS" nil)
      (setq name (strcat "PALC_CLEAN_" (itoa (getvar "MILLISECS"))) count 0)
      (while (tblsearch "BLOCK" name)
        (setq count (1+ count) name (strcat name "_" (itoa count))))
      (PALC:title-style)
      (PALC:build name)
      (setq entity
        (entmakex
          (list '(0 . "INSERT") '(100 . "AcDbEntity") '(8 . "PALC_01_STRUCTURE")
                '(62 . 7) '(420 . 0) '(370 . 18) '(100 . "AcDbBlockReference")
                (cons 2 name) (cons 10 base) (cons 41 factor) (cons 42 factor)
                (cons 43 factor) '(50 . 0.0))))
      (if (null entity) (progn (princ "\nUnable to insert facade block.") (quit)))
      (setq PALC:LAST (list entity base factor nil))
      (setvar "INSUNITS" 4) (setvar "LWDISPLAY" 1) (setvar "FILLMODE" 1)
      (initget "Yes No")
      (setq dims (getkword "\nAdd estimated overall dimensions? [Yes/No] <No>: "))
      (if (equal dims "Yes") (setq PALC:LAST (PALC:dimensions PALC:LAST)))
      (vla-Regen doc 1)
      (vl-catch-all-apply 'vla-ZoomWindow
        (list acad
          (vlax-3d-point (PALC:point '(-2412.2137 -1175.5725) base factor))
          (vlax-3d-point (PALC:point '(16213.7405 12015.2672) base factor))))
      (vla-EndUndoMark doc) (setq mark nil)
      (princ (strcat "\nFacade complete. Estimated width: " (rtos width 2 0)
                     " mm; estimated height: " (rtos (* factor 10610.687) 2 0)
                     " mm. One UNDO removes this insertion and its dimensions."))))
  (princ))

(defun c:PALACEDIMS (/ *error* doc mark)
  (setq doc (vla-get-ActiveDocument (vlax-get-acad-object)) mark nil)
  (defun *error* (message)
    (if mark (vl-catch-all-apply 'vla-EndUndoMark (list doc)))
    (princ (strcat "\nDimension command stopped: " message)) (princ))
  (if (and PALC:LAST (entget (car PALC:LAST)))
    (progn (vla-StartUndoMark doc) (setq mark T)
      (setq PALC:LAST (PALC:dimensions PALC:LAST))
      (vla-Regen doc 1) (vla-EndUndoMark doc) (setq mark nil)
      (princ "\nEstimated dimensions updated for the last facade insertion."))
    (princ "\nRun PALACE first."))
  (princ))

(defun c:PALACEINFO ()
  (princ "\nPALACE = draw self-contained facade; PALACEDIMS = native overall dimensions.")
  (princ "\nUnits are mm. Default estimated width 14000 mm; height 10610.687 mm.")
  (princ "\nBlack outlines 0.18 mm. Shared edges once, no loose ends; intentional joints remain.")
  (princ "\nThe reference is visually reconstructed; dimensions are estimated, not surveyed.")
  (princ))

(setq PALC:LAST nil)
(setq PALC:LAYERS
  '("01_STRUCTURE" "02_CORNICES" "03_FRAMES_DOORS" "04_GLAZING_SHUTTERS"
    "05_STONE_JOINTS" "06_ORNAMENT" "07_RAILINGS" "08_STEPS" "10_REFERENCE_TITLE"))

(defun c:PALACESIZES (/ factor row width height)
  (setq factor (if PALC:LAST (caddr PALC:LAST) 1.0))
  (princ "\nEstimated dimensions in mm, scaled for the last insertion:")
  (foreach row PALC:SIZES
    (setq width (cadr row) height (caddr row))
    (princ (strcat "\n" (car row)
      (if width (strcat " | width=" (rtos (* factor width) 2 0)) "")
      (if height (strcat " | height/level=" (rtos (* factor height) 2 0)) ""))))
  (princ))

(defun PALC:title-style ()
  (if (null (tblsearch "STYLE" "PALC_REFERENCE_ARIAL"))
    (PALC:emit
      '((0 . "STYLE") (100 . "AcDbSymbolTableRecord") (100 . "AcDbTextStyleTableRecord")
        (2 . "PALC_REFERENCE_ARIAL") (70 . 0) (40 . 0.0) (41 . 1.0) (50 . 0.0)
        (71 . 0) (42 . 0.0) (3 . "arial.ttf") (4 . "")))))

(setq PALC:DIMS
  '(
    ((0.0 10610.687) (14000.0 8076.3359) (7000.0 11610.687) 0.000000000000000)
    ((-381.6794 0.0) (0.0 10610.687) (-1300.0 5305.3435) 1.570796326794897)
  ))

; Each row: (layer closed-flag ((x y) ...)), in nominal estimated millimetres.
(setq PALC:DATA
  '(
    ; P0001 -- see feature_dimensions_mm.csv
    ("01_STRUCTURE" 0 (
      (4992.3664 9587.7863) (183.2061 9587.7863)
    ))
    ; P0002 -- see feature_dimensions_mm.csv
    ("01_STRUCTURE" 0 (
      (183.2061 5801.5267) (183.2061 5725.1908)
    ))
    ; P0003 -- see feature_dimensions_mm.csv
    ("01_STRUCTURE" 0 (
      (183.2061 5541.9847) (183.2061 5206.1069) (183.2061 5129.771) (183.2061 5053.4351) (183.2061 4961.8321)
      (183.2061 4870.229) (183.2061 4534.3511) (183.2061 4458.0153) (183.2061 4381.6794) (183.2061 4290.0763)
      (183.2061 4198.4733) (183.2061 3862.5954) (183.2061 3786.2595)
    ))
    ; P0004 -- see feature_dimensions_mm.csv
    ("01_STRUCTURE" 0 (
      (183.2061 2946.5649) (183.2061 2854.9618) (183.2061 2519.084) (183.2061 2442.7481) (183.2061 2366.4122)
      (183.2061 2274.8092) (183.2061 2183.2061) (183.2061 1847.3282) (183.2061 1770.9924)
    ))
    ; P0005 -- see feature_dimensions_mm.csv
    ("01_STRUCTURE" 0 (
      (183.2061 1694.6565) (183.2061 1603.0534)
    ))
    ; P0006 -- see feature_dimensions_mm.csv
    ("01_STRUCTURE" 0 (
      (183.2061 809.1603) (183.2061 0.0) (961.8321 0.0)
    ))
    ; P0007 -- see feature_dimensions_mm.csv
    ("01_STRUCTURE" 0 (
      (961.8321 7526.7176) (961.8321 7221.374)
    ))
    ; P0008 -- see feature_dimensions_mm.csv
    ("01_STRUCTURE" 0 (
      (961.8321 6564.8855) (961.8321 6549.6183) (961.8321 6473.2824) (961.8321 6396.9466) (961.8321 6305.3435)
    ))
    ; P0009 -- see feature_dimensions_mm.csv
    ("01_STRUCTURE" 0 (
      (961.8321 3862.5954) (961.8321 4198.4733) (961.8321 4290.0763) (961.8321 4381.6794) (961.8321 4458.0153)
      (961.8321 4534.3511) (961.8321 4870.229) (961.8321 4961.8321) (961.8321 5053.4351) (961.8321 5129.771)
      (961.8321 5206.1069) (961.8321 5465.6489)
    ))
    ; P0010 -- see feature_dimensions_mm.csv
    ("01_STRUCTURE" 0 (
      (961.8321 3664.1221) (1358.7786 3664.1221) (1358.7786 3633.5878)
    ))
    ; P0011 -- see feature_dimensions_mm.csv
    ("01_STRUCTURE" 0 (
      (4992.3664 3267.1756) (961.8321 3267.1756)
    ))
    ; P0012 -- see feature_dimensions_mm.csv
    ("01_STRUCTURE" 0 (
      (4595.4198 5465.6489) (4595.4198 5816.7939) (4595.4198 5969.4656) (4595.4198 6015.2672) (4351.145 6015.2672)
      (4351.145 6244.2748) (1603.0534 6244.2748) (1603.0534 6015.2672) (1358.7786 6015.2672) (1358.7786 5969.4656)
    ))
    ; P0013 -- see feature_dimensions_mm.csv
    ("01_STRUCTURE" 0 (
      (1730.6718 2155.7252) (1711.8321 2122.5954)
    ))
    ; P0014 -- see feature_dimensions_mm.csv
    ("01_STRUCTURE" 0 (
      (1827.7252 2274.6107) (1800.3969 2247.1908)
    ))
    ; P0015 -- see feature_dimensions_mm.csv
    ("01_STRUCTURE" 0 (
      (2061.0687 2961.8321) (2061.0687 2809.1603) (1938.9313 2809.1603) (1938.9313 2961.8321)
    ))
    ; P0016 -- see feature_dimensions_mm.csv
    ("01_STRUCTURE" 0 (
      (2140.3969 2431.7252) (2101.4809 2423.1908)
    ))
    ; P0017 -- see feature_dimensions_mm.csv
    ("01_STRUCTURE" 0 (
      (2351.145 2961.8321) (2351.145 2809.1603) (2229.0076 2809.1603) (2229.0076 2961.8321)
    ))
    ; P0018 -- see feature_dimensions_mm.csv
    ("01_STRUCTURE" 0 (
      (2564.8855 2365.8473) (2529.6489 2383.542)
    ))
    ; P0019 -- see feature_dimensions_mm.csv
    ("01_STRUCTURE" 0 (
      (2631.2977 2324.1221) (2598.8244 2346.0)
    ))
    ; P0020 -- see feature_dimensions_mm.csv
    ("01_STRUCTURE" 0 (
      (2788.4122 2155.7252) (2767.313 2187.6183)
    ))
    ; P0021 -- see feature_dimensions_mm.csv
    ("01_STRUCTURE" 0 (
      (2823.7405 2088.3817) (2834.6718 2061.0687) (3190.8397 2061.0687)
    ))
    ; P0022 -- see feature_dimensions_mm.csv
    ("01_STRUCTURE" 0 (
      (2824.4275 656.4885) (2870.229 656.4885) (3129.771 656.4885) (3129.771 931.2977) (3129.771 1282.4427)
      (3129.771 1633.5878)
    ))
    ; P0023 -- see feature_dimensions_mm.csv
    ("01_STRUCTURE" 0 (
      (2865.0076 1943.6336) (2858.4885 1980.687)
    ))
    ; P0024 -- see feature_dimensions_mm.csv
    ("01_STRUCTURE" 0 (
      (2946.5649 1862.5954) (2870.229 1862.5954)
    ))
    ; P0025 -- see feature_dimensions_mm.csv
    ("01_STRUCTURE" 0 (
      (3114.5038 1969.4656) (3114.5038 1862.5954)
    ))
    ; P0026 -- see feature_dimensions_mm.csv
    ("01_STRUCTURE" 0 (
      (3221.374 2030.5344) (3221.374 1984.7328) (3221.374 1633.5878) (3221.374 1282.4427) (3221.374 931.2977)
      (3221.374 656.4885) (3221.374 442.7481)
    ))
    ; P0027 -- see feature_dimensions_mm.csv
    ("01_STRUCTURE" 0 (
      (3566.5038 2472.9466) (3537.3435 2464.2443) (3508.8244 2453.6794)
    ))
    ; P0028 -- see feature_dimensions_mm.csv
    ("01_STRUCTURE" 0 (
      (3574.3053 2474.7328) (3541.9847 2625.9542)
    ))
    ; P0029 -- see feature_dimensions_mm.csv
    ("01_STRUCTURE" 0 (
      (4056.4427 2309.3588) (4037.1145 2332.5191) (4016.2901 2354.3969) (3994.0458 2374.8855) (3970.4885 2393.9084)
      (3945.7252 2411.3588) (3919.8473 2427.1908) (3892.9771 2441.313) (3865.2214 2453.6794) (3836.7023 2464.2443)
      (3807.542 2472.9466) (3799.7405 2474.7328) (3832.0611 2625.9542)
    ))
    ; P0030 -- see feature_dimensions_mm.csv
    ("01_STRUCTURE" 0 (
      (4183.2061 2061.0687) (4732.8244 2061.0687)
    ))
    ; P0031 -- see feature_dimensions_mm.csv
    ("01_STRUCTURE" 0 (
      (4290.0763 1969.4656) (4351.145 1862.5954) (4244.2748 1862.5954) (4244.2748 1633.5878)
    ))
    ; P0032 -- see feature_dimensions_mm.csv
    ("01_STRUCTURE" 0 (
      (4244.2748 1282.4427) (4244.2748 931.2977) (4244.2748 656.4885)
    ))
    ; P0033 -- see feature_dimensions_mm.csv
    ("01_STRUCTURE" 0 (
      (4519.084 656.4885) (4519.084 931.2977) (4519.084 1282.4427) (4519.084 1633.5878) (4519.084 1862.5954)
      (4656.4885 1862.5954) (4656.4885 1969.4656)
    ))
    ; P0034 -- see feature_dimensions_mm.csv
    ("01_STRUCTURE" 0 (
      (4595.4198 5465.6489) (4671.7557 5465.6489) (4691.6031 5465.6489) (4763.3588 5465.6489) (4783.2061 5465.6489)
      (4854.9618 5465.6489) (4874.8092 5465.6489) (4946.5649 5465.6489) (4966.4122 5465.6489) (4992.3664 5465.6489)
    ))
    ; P0035 -- see feature_dimensions_mm.csv
    ("01_STRUCTURE" 0 (
      (4595.4198 5007.6336) (4595.4198 5465.6489)
    ))
    ; P0036 -- see feature_dimensions_mm.csv
    ("01_STRUCTURE" 0 (
      (4992.3664 3740.458) (4595.4198 3740.458)
    ))
    ; P0037 -- see feature_dimensions_mm.csv
    ("01_STRUCTURE" 0 (
      (4992.3664 3664.1221) (4595.4198 3664.1221)
    ))
    ; P0038 -- see feature_dimensions_mm.csv
    ("01_STRUCTURE" 0 (
      (4992.3664 7541.9847) (4992.3664 7526.7176)
    ))
    ; P0039 -- see feature_dimensions_mm.csv
    ("01_STRUCTURE" 0 (
      (4992.3664 7312.9771) (4992.3664 6992.3664)
    ))
    ; P0040 -- see feature_dimensions_mm.csv
    ("01_STRUCTURE" 0 (
      (4992.3664 6961.8321) (5007.6336 6961.8321) (5068.7023 6961.8321) (5099.2366 6961.8321) (5160.3053 6961.8321)
    ))
    ; P0041 -- see feature_dimensions_mm.csv
    ("01_STRUCTURE" 0 (
      (4992.3664 6564.8855) (4992.3664 6473.2824) (4992.3664 5969.4656) (4992.3664 5816.7939) (4992.3664 5465.6489)
    ))
    ; P0042 -- see feature_dimensions_mm.csv
    ("01_STRUCTURE" 0 (
      (4992.3664 5465.6489) (4992.3664 5343.5115) (4992.3664 4717.5573) (4992.3664 4091.6031) (4992.3664 3740.458)
    ))
    ; P0043 -- see feature_dimensions_mm.csv
    ("01_STRUCTURE" 0 (
      (4992.3664 3740.458) (4992.3664 3679.3893) (4992.3664 3664.1221)
    ))
    ; P0044 -- see feature_dimensions_mm.csv
    ("01_STRUCTURE" 0 (
      (4992.3664 3664.1221) (4992.3664 3633.5878)
    ))
    ; P0045 -- see feature_dimensions_mm.csv
    ("01_STRUCTURE" 0 (
      (5175.5725 3267.1756) (4992.3664 3267.1756)
    ))
    ; P0046 -- see feature_dimensions_mm.csv
    ("01_STRUCTURE" 0 (
      (4992.3664 3267.1756) (4992.3664 2961.8321) (4992.3664 2839.6947)
    ))
    ; P0047 -- see feature_dimensions_mm.csv
    ("01_STRUCTURE" 0 (
      (4992.3664 1984.7328) (4992.3664 1633.5878) (4992.3664 1587.7863) (4992.3664 1282.4427) (4992.3664 961.8321)
      (4992.3664 931.2977) (4992.3664 793.8931) (4992.3664 656.4885)
    ))
    ; P0048 -- see feature_dimensions_mm.csv
    ("01_STRUCTURE" 0 (
      (4992.3664 0.0) (8671.7557 0.0) (8671.7557 15.2672) (8671.7557 122.1374) (8671.7557 213.7405)
      (8671.7557 290.0763)
    ))
    ; P0049 -- see feature_dimensions_mm.csv
    ("01_STRUCTURE" 0 (
      (5175.5725 3633.5878) (5175.5725 3465.6489)
    ))
    ; P0050 -- see feature_dimensions_mm.csv
    ("01_STRUCTURE" 0 (
      (5221.374 3465.6489) (5221.374 4091.6031) (5221.374 4717.5573) (5221.374 5343.5115) (5221.374 5358.7786)
      (5222.3359 5387.7405) (5225.2214 5416.5649) (5230.0305 5445.1603) (5236.7176 5473.374) (5245.2824 5501.0992)
      (5255.6641 5528.2137) (5267.8168 5554.5954) (5281.7099 5580.1527) (5297.2824 5604.7634) (5314.4427 5628.3053)
      (5333.145 5650.7023) (5353.2824 5671.8473) (5374.7939 5691.6489) (5397.5878 5710.0305) (5421.542 5726.916)
      (5446.5649 5742.2137) (5472.5496 5755.8626) (5499.4046 5767.8321) (5526.9924 5778.0305) (5555.1908 5786.4427)
      (5583.8931 5793.0229) (5612.9618 5797.7405) (5642.3053 5800.5802) (5671.7557 5801.5267) (5701.2061 5800.5802)
      (5730.5496 5797.7405) (5759.6183 5793.0229) (5788.3206 5786.4427) (5816.5191 5778.0305) (5844.1069 5767.8321)
      (5870.9618 5755.8626) (5896.9466 5742.2137) (5921.9695 5726.916) (5945.9237 5710.0305) (5968.7176 5691.6489)
      (5990.229 5671.8473) (6010.3664 5650.7023) (6029.0687 5628.3053) (6046.229 5604.7634) (6061.8015 5580.1527)
      (6075.6947 5554.5954) (6087.8473 5528.2137) (6098.229 5501.0992) (6106.7939 5473.374) (6113.4809 5445.1603)
      (6118.2901 5416.5649) (6121.1756 5387.7405) (6122.1374 5358.7786) (6122.1374 5343.5115) (6122.1374 4717.5573)
      (6122.1374 4091.6031) (6122.1374 3465.6489)
    ))
    ; P0051 -- see feature_dimensions_mm.csv
    ("01_STRUCTURE" 0 (
      (6122.1374 2839.6947) (6122.1374 2213.7405) (6122.1374 1587.7863) (6122.1374 1099.2366) (6122.1374 1053.4351)
      (6096.687 1053.4351) (5246.8244 1053.4351) (5221.374 1053.4351) (5221.374 1099.2366) (5221.374 1587.7863)
      (5221.374 2213.7405) (5221.374 2839.6947)
    ))
    ; P0052 -- see feature_dimensions_mm.csv
    ("01_STRUCTURE" 0 (
      (6259.542 3465.6489) (6259.542 4091.6031) (6259.542 4717.5573) (6259.542 5343.5115) (6259.542 5358.7786)
      (6260.855 5387.7405) (6264.7634 5416.5649) (6271.2824 5445.1603) (6280.3511 5473.374) (6291.9542 5501.0992)
      (6306.0305 5528.2137) (6322.5191 5554.5954) (6341.3588 5580.1527) (6362.458 5604.7634) (6385.7405 5628.3053)
      (6411.084 5650.7023) (6438.4122 5671.8473) (6467.5725 5691.6489) (6498.4733 5710.0305) (6530.9466 5726.916)
      (6564.8855 5742.2137) (6600.1221 5755.8626) (6636.5344 5767.8321) (6673.9237 5778.0305) (6712.1679 5786.4427)
      (6751.084 5793.0229) (6790.5191 5797.7405) (6830.2901 5800.5802) (6870.229 5801.5267) (6910.1679 5800.5802)
      (6949.9389 5797.7405) (6989.374 5793.0229) (7028.2901 5786.4427) (7066.5344 5778.0305) (7103.9237 5767.8321)
      (7140.3359 5755.8626) (7175.5725 5742.2137) (7209.5115 5726.916) (7241.9847 5710.0305) (7272.8855 5691.6489)
      (7302.0458 5671.8473) (7329.374 5650.7023) (7354.7176 5628.3053) (7378.0 5604.7634) (7399.0992 5580.1527)
      (7417.9389 5554.5954) (7434.4275 5528.2137) (7448.5038 5501.0992) (7460.1069 5473.374) (7469.1756 5445.1603)
      (7475.6947 5416.5649) (7479.6031 5387.7405) (7480.916 5358.7786) (7480.916 5343.5115) (7480.916 4717.5573)
    ))
    ; P0053 -- see feature_dimensions_mm.csv
    ("01_STRUCTURE" 0 (
      (7480.916 2213.7405) (7480.916 1587.7863) (7480.916 1099.2366) (7480.916 1053.4351) (7455.4656 1053.4351)
      (6284.9924 1053.4351) (6259.542 1053.4351) (6259.542 1099.2366) (6259.542 1587.7863) (6259.542 2213.7405)
      (6259.542 2839.6947)
    ))
    ; P0054 -- see feature_dimensions_mm.csv
    ("01_STRUCTURE" 0 (
      (7618.3206 2839.6947) (7618.3206 3465.6489) (7618.3206 4091.6031) (7618.3206 4717.5573) (7618.3206 5343.5115)
      (7618.3206 5358.7786) (7619.2824 5387.7405) (7622.1679 5416.5649) (7626.9771 5445.1603) (7633.6641 5473.374)
      (7642.229 5501.0992) (7652.6107 5528.2137) (7664.7634 5554.5954)
    ))
    ; P0055 -- see feature_dimensions_mm.csv
    ("01_STRUCTURE" 0 (
      (8473.2824 1053.4351) (7643.771 1053.4351) (7618.3206 1053.4351) (7618.3206 1099.2366) (7618.3206 1587.7863)
    ))
    ; P0056 -- see feature_dimensions_mm.csv
    ("01_STRUCTURE" 0 (
      (7678.6565 5580.1527) (7694.229 5604.7634) (7711.3893 5628.3053)
    ))
    ; P0057 -- see feature_dimensions_mm.csv
    ("01_STRUCTURE" 0 (
      (7730.0916 5650.7023) (7750.229 5671.8473)
    ))
    ; P0058 -- see feature_dimensions_mm.csv
    ("01_STRUCTURE" 0 (
      (7771.7405 5691.6489) (7794.5344 5710.0305) (7818.4885 5726.916) (7843.5115 5742.2137) (7869.4962 5755.8626)
      (7896.3511 5767.8321) (7923.9389 5778.0305) (7952.1374 5786.4427)
    ))
    ; P0059 -- see feature_dimensions_mm.csv
    ("01_STRUCTURE" 0 (
      (7980.8397 5793.0229) (8009.9084 5797.7405) (8039.2519 5800.5802) (8068.7023 5801.5267) (8098.1527 5800.5802)
    ))
    ; P0060 -- see feature_dimensions_mm.csv
    ("01_STRUCTURE" 0 (
      (8127.4962 5797.7405) (8156.5649 5793.0229) (8185.2672 5786.4427) (8213.4656 5778.0305) (8241.0534 5767.8321)
      (8267.9084 5755.8626) (8293.8931 5742.2137) (8318.916 5726.916) (8342.8702 5710.0305) (8365.6641 5691.6489)
      (8387.1756 5671.8473) (8407.313 5650.7023) (8426.0153 5628.3053)
    ))
    ; P0061 -- see feature_dimensions_mm.csv
    ("01_STRUCTURE" 0 (
      (8303.1603 6961.8321) (8335.8779 6961.8321)
    ))
    ; P0062 -- see feature_dimensions_mm.csv
    ("01_STRUCTURE" 0 (
      (8366.4122 6961.8321) (8427.4809 6961.8321) (8458.0153 6961.8321) (8519.084 6961.8321) (8549.6183 6961.8321)
      (8579.0687 6961.8321) (8610.687 6961.8321) (8641.2214 6961.8321) (8671.7557 6961.8321)
    ))
    ; P0063 -- see feature_dimensions_mm.csv
    ("01_STRUCTURE" 0 (
      (8443.1756 5604.7634) (8458.7481 5580.1527) (8472.6412 5554.5954) (8484.7939 5528.2137) (8495.1756 5501.0992)
      (8503.7405 5473.374) (8510.4275 5445.1603) (8515.2366 5416.5649) (8518.1221 5387.7405)
    ))
    ; P0064 -- see feature_dimensions_mm.csv
    ("01_STRUCTURE" 0 (
      (8671.7557 290.0763) (8519.084 290.0763) (8473.2824 290.0763) (8473.2824 793.8931) (8473.2824 961.8321)
      (8473.2824 1016.7939)
    ))
    ; P0065 -- see feature_dimensions_mm.csv
    ("01_STRUCTURE" 0 (
      (8519.084 5358.7786) (8519.084 5343.5115) (8519.084 4717.5573) (8519.084 4091.6031) (8519.084 3618.3206)
      (8671.7557 3618.3206)
    ))
    ; P0066 -- see feature_dimensions_mm.csv
    ("01_STRUCTURE" 0 (
      (10122.1374 7923.6641) (8671.7557 7923.6641)
    ))
    ; P0067 -- see feature_dimensions_mm.csv
    ("01_STRUCTURE" 0 (
      (8671.7557 6961.8321) (8671.7557 7312.9771)
    ))
    ; P0068 -- see feature_dimensions_mm.csv
    ("01_STRUCTURE" 0 (
      (8671.7557 3618.3206) (8671.7557 4091.6031) (8671.7557 4717.5573) (8671.7557 5343.5115) (8671.7557 5969.4656)
      (8671.7557 6473.2824) (8671.7557 6625.9542) (8671.7557 6961.8321)
    ))
    ; P0069 -- see feature_dimensions_mm.csv
    ("01_STRUCTURE" 0 (
      (8671.7557 3618.3206) (8687.0229 3618.3206) (8687.0229 4473.2824) (8793.8931 4473.2824)
    ))
    ; P0070 -- see feature_dimensions_mm.csv
    ("01_STRUCTURE" 0 (
      (8671.7557 290.0763) (10290.0763 290.0763) (10412.2137 290.0763) (10519.084 290.0763) (10519.084 656.4885)
    ))
    ; P0071 -- see feature_dimensions_mm.csv
    ("01_STRUCTURE" 0 (
      (8778.626 4412.2137) (8748.0916 4412.2137) (8748.0916 3832.0611) (8778.626 3832.0611) (8793.8931 3832.0611)
      (8793.8931 4412.2137)
    ))
    ; P0072 -- see feature_dimensions_mm.csv
    ("01_STRUCTURE" 0 (
      (8803.8473 5405.0076) (8815.771 5426.7328)
    ))
    ; P0073 -- see feature_dimensions_mm.csv
    ("01_STRUCTURE" 0 (
      (9334.4733 5653.2214) (9369.5573 5660.0916) (9402.855 5666.1374) (9434.0153 5671.374)
    ))
    ; P0074 -- see feature_dimensions_mm.csv
    ("01_STRUCTURE" 0 (
      (9488.5496 5679.3893) (9514.3969 5675.7863) (9543.084 5671.374) (9574.2443 5666.1374) (9607.542 5660.0916)
      (9642.626 5653.2214) (9679.145 5645.5267) (9716.7481 5636.9924) (9755.0992 5627.6183) (9793.8168 5617.3893)
      (9832.5802 5606.3206) (9871.0382 5594.3969) (9908.8244 5581.6031) (9945.5878 5567.9389) (9981.0076 5553.4046)
      (10014.7023 5538.0) (10046.3359 5521.6947) (10075.5573 5504.5038) (10102.0153 5486.4275) (10125.374 5467.4351)
    ))
    ; P0075 -- see feature_dimensions_mm.csv
    ("01_STRUCTURE" 0 (
      (9584.1221 2381.6794) (9408.2443 2381.6794) (9383.9389 2509.2519) (9358.7786 2641.2214) (9633.5878 2641.2214)
      (9608.4427 2509.2519)
    ))
    ; P0076 -- see feature_dimensions_mm.csv
    ("01_STRUCTURE" 0 (
      (10290.0763 7541.9847) (10122.1374 7541.9847) (10122.1374 7740.458)
    ))
    ; P0077 -- see feature_dimensions_mm.csv
    ("01_STRUCTURE" 0 (
      (10183.2061 5358.7786) (10183.2061 4473.2824) (10290.0763 4473.2824)
    ))
    ; P0078 -- see feature_dimensions_mm.csv
    ("01_STRUCTURE" 0 (
      (10183.2061 4412.2137) (10183.2061 3832.0611)
    ))
    ; P0079 -- see feature_dimensions_mm.csv
    ("01_STRUCTURE" 0 (
      (10198.4733 3832.0611) (10229.0076 3832.0611) (10229.0076 4412.2137) (10198.4733 4412.2137)
    ))
    ; P0080 -- see feature_dimensions_mm.csv
    ("01_STRUCTURE" 0 (
      (10290.0763 6992.3664) (10290.0763 7526.7176)
    ))
    ; P0081 -- see feature_dimensions_mm.csv
    ("01_STRUCTURE" 0 (
      (10290.0763 5465.6489) (10290.0763 5816.7939) (10290.0763 5969.4656) (10290.0763 6564.8855)
    ))
    ; P0082 -- see feature_dimensions_mm.csv
    ("01_STRUCTURE" 0 (
      (10290.0763 5465.6489) (10366.4122 5465.6489) (10386.2595 5465.6489) (10458.0153 5465.6489) (10477.8626 5465.6489)
      (10549.6183 5465.6489) (10569.4656 5465.6489) (10641.2214 5465.6489) (10661.0687 5465.6489) (10687.0229 5465.6489)
      (10687.0229 5362.1832) (10687.0229 5355.8168)
    ))
    ; P0083 -- see feature_dimensions_mm.csv
    ("01_STRUCTURE" 0 (
      (10290.0763 4473.2824) (10290.0763 5465.6489)
    ))
    ; P0084 -- see feature_dimensions_mm.csv
    ("01_STRUCTURE" 0 (
      (10687.0229 3740.458) (10290.0763 3740.458) (10290.0763 4473.2824)
    ))
    ; P0085 -- see feature_dimensions_mm.csv
    ("01_STRUCTURE" 0 (
      (10687.0229 3664.1221) (10335.8779 3664.1221) (10290.0763 3664.1221)
    ))
    ; P0086 -- see feature_dimensions_mm.csv
    ("01_STRUCTURE" 0 (
      (10290.0763 15.2672) (10290.0763 0.0) (13832.0611 0.0) (13832.0611 656.4885)
    ))
    ; P0087 -- see feature_dimensions_mm.csv
    ("01_STRUCTURE" 0 (
      (10519.084 2061.0687) (10519.084 2305.3435) (10519.084 2641.2214) (10519.084 2961.8321) (10519.084 3267.1756)
      (10519.084 3282.4427) (10519.084 3297.7099) (10519.084 3389.313) (10519.084 3618.3206)
    ))
    ; P0088 -- see feature_dimensions_mm.csv
    ("01_STRUCTURE" 0 (
      (10811.0687 2122.5954) (10794.5802 2088.3817) (10783.6489 2061.0687) (10519.084 2061.0687)
    ))
    ; P0089 -- see feature_dimensions_mm.csv
    ("01_STRUCTURE" 0 (
      (10519.084 1984.7328) (10519.084 2008.7176) (10519.084 2061.0687)
    ))
    ; P0090 -- see feature_dimensions_mm.csv
    ("01_STRUCTURE" 0 (
      (10564.8855 1969.4656) (10610.687 1862.5954)
    ))
    ; P0091 -- see feature_dimensions_mm.csv
    ("01_STRUCTURE" 0 (
      (13190.8397 6244.2748) (10931.2977 6244.2748) (10931.2977 6155.6183) (10931.2977 6015.2672) (10891.771 6015.2672)
      (10687.0229 6015.2672) (10687.0229 5969.4656) (10687.0229 5816.7939) (10687.0229 5605.2519)
    ))
    ; P0092 -- see feature_dimensions_mm.csv
    ("01_STRUCTURE" 0 (
      (10687.0229 4485.5878) (10687.0229 4316.4733) (10687.0229 4223.4809) (10687.0229 4222.0763) (10687.0229 4209.0229)
      (10687.0229 4187.8321) (10687.0229 4164.9008) (10687.0229 4152.5344) (10687.0229 4122.8855) (10687.0229 4100.229)
      (10687.0229 4099.2061) (10687.0229 4096.6718) (10687.0229 4076.7328)
    ))
    ; P0093 -- see feature_dimensions_mm.csv
    ("01_STRUCTURE" 0 (
      (10956.1221 2300.2901) (10926.9618 2274.6107) (10899.6336 2247.1908) (10874.2901 2218.1527) (10851.0076 2187.6183)
      (10829.9084 2155.7252)
    ))
    ; P0094 -- see feature_dimensions_mm.csv
    ("01_STRUCTURE" 0 (
      (11053.4351 2365.8473) (11019.4962 2346.0)
    ))
    ; P0095 -- see feature_dimensions_mm.csv
    ("01_STRUCTURE" 0 (
      (11249.4351 2433.2366) (11239.6336 2431.7252) (11200.7176 2423.1908) (11162.4733 2412.2901) (11125.084 2399.0534)
      (11088.6718 2383.542)
    ))
    ; P0096 -- see feature_dimensions_mm.csv
    ("01_STRUCTURE" 0 (
      (11213.7405 2610.687) (11503.8168 2610.687)
    ))
    ; P0097 -- see feature_dimensions_mm.csv
    ("01_STRUCTURE" 0 (
      (11477.9237 2431.7252) (11468.1221 2433.2366)
    ))
    ; P0098 -- see feature_dimensions_mm.csv
    ("01_STRUCTURE" 0 (
      (11664.1221 2365.8473) (11628.8855 2383.542) (11592.4733 2399.0534) (11555.084 2412.2901) (11516.8397 2423.1908)
    ))
    ; P0099 -- see feature_dimensions_mm.csv
    ("01_STRUCTURE" 0 (
      (11730.5344 2324.1221) (11698.0611 2346.0)
    ))
    ; P0100 -- see feature_dimensions_mm.csv
    ("01_STRUCTURE" 0 (
      (11933.9084 2061.0687) (11922.9771 2088.3817) (11906.4885 2122.5954) (11887.6489 2155.7252) (11866.5496 2187.6183)
      (11843.2672 2218.1527) (11817.9237 2247.1908) (11790.5954 2274.6107) (11761.4351 2300.2901)
    ))
    ; P0101 -- see feature_dimensions_mm.csv
    ("01_STRUCTURE" 0 (
      (11968.1527 1906.2443) (11964.2443 1943.6336) (11963.5267 1947.6947) (12000.0 1862.5954) (11969.4656 1862.5954)
      (11969.4656 1868.7023)
    ))
    ; P0102 -- see feature_dimensions_mm.csv
    ("01_STRUCTURE" 0 (
      (11969.4656 656.4885) (12091.6031 656.4885) (12198.4733 656.4885) (12213.7405 656.4885)
    ))
    ; P0103 -- see feature_dimensions_mm.csv
    ("01_STRUCTURE" 0 (
      (12583.145 2431.7252) (12544.229 2423.1908)
    ))
    ; P0104 -- see feature_dimensions_mm.csv
    ("01_STRUCTURE" 0 (
      (13007.6336 2365.8473) (12972.3969 2383.542)
    ))
    ; P0105 -- see feature_dimensions_mm.csv
    ("01_STRUCTURE" 0 (
      (13074.0458 2324.1221) (13041.5725 2346.0)
    ))
    ; P0106 -- see feature_dimensions_mm.csv
    ("01_STRUCTURE" 0 (
      (13277.4198 2061.0687) (13801.5267 2061.0687)
    ))
    ; P0107 -- see feature_dimensions_mm.csv
    ("01_STRUCTURE" 0 (
      (13300.2443 1984.7328) (13293.3588 2012.4427)
    ))
    ; P0108 -- see feature_dimensions_mm.csv
    ("01_STRUCTURE" 0 (
      (13832.0611 5465.6489) (13435.1145 5465.6489) (13435.1145 5605.2519) (13435.1145 5969.4656)
    ))
    ; P0109 -- see feature_dimensions_mm.csv
    ("01_STRUCTURE" 0 (
      (13832.0611 5465.6489) (13832.0611 3740.458) (13435.1145 3740.458)
    ))
    ; P0110 -- see feature_dimensions_mm.csv
    ("01_STRUCTURE" 0 (
      (13832.0611 3633.5878) (13832.0611 3664.1221) (13435.1145 3664.1221)
    ))
    ; P0111 -- see feature_dimensions_mm.csv
    ("01_STRUCTURE" 0 (
      (13725.1908 1862.5954) (13557.2519 1862.5954)
    ))
    ; P0112 -- see feature_dimensions_mm.csv
    ("01_STRUCTURE" 0 (
      (13557.2519 931.2977) (13557.2519 1282.4427)
    ))
    ; P0113 -- see feature_dimensions_mm.csv
    ("01_STRUCTURE" 0 (
      (13832.0611 5465.6489) (13832.0611 5969.4656) (13832.0611 6564.8855)
    ))
    ; P0114 -- see feature_dimensions_mm.csv
    ("01_STRUCTURE" 0 (
      (13832.0611 2961.8321) (13832.0611 3267.1756)
    ))
    ; P0115 -- see feature_dimensions_mm.csv
    ("01_STRUCTURE" 0 (
      (13832.0611 1984.7328) (13832.0611 2305.3435)
    ))
    ; P0116 -- see feature_dimensions_mm.csv
    ("01_STRUCTURE" 0 (
      (13832.0611 931.2977) (13832.0611 1282.4427)
    ))
    ; P0117 -- see feature_dimensions_mm.csv
    ("01_STRUCTURE" 1 (
      (2519.084 3099.2366) (2641.2214 3099.2366) (2641.2214 2961.8321) (2641.2214 2809.1603) (2519.084 2809.1603)
      (2519.084 2961.8321)
    ))
    ; P0118 -- see feature_dimensions_mm.csv
    ("01_STRUCTURE" 1 (
      (3343.5115 3099.2366) (3465.6489 3099.2366) (3465.6489 2961.8321) (3465.6489 2809.1603) (3343.5115 2809.1603)
      (3343.5115 2961.8321)
    ))
    ; P0119 -- see feature_dimensions_mm.csv
    ("01_STRUCTURE" 1 (
      (3633.5878 3099.2366) (3755.7252 3099.2366) (3755.7252 2961.8321) (3755.7252 2809.1603) (3633.5878 2809.1603)
      (3633.5878 2961.8321)
    ))
    ; P0120 -- see feature_dimensions_mm.csv
    ("01_STRUCTURE" 1 (
      (3923.6641 3099.2366) (4045.8015 3099.2366) (4045.8015 2961.8321) (4045.8015 2809.1603) (3923.6641 2809.1603)
      (3923.6641 2961.8321)
    ))
    ; P0121 -- see feature_dimensions_mm.csv
    ("02_CORNICES" 0 (
      (5160.3053 10259.542) (0.0 10259.542)
    ))
    ; P0122 -- see feature_dimensions_mm.csv
    ("02_CORNICES" 0 (
      (122.1374 10122.1374) (106.8702 10122.1374) (0.0 10259.542)
    ))
    ; P0123 -- see feature_dimensions_mm.csv
    ("02_CORNICES" 0 (
      (0.0 10259.542) (0.0 10610.687) (245.7252 10610.687) (272.5344 10525.1908) (299.3435 10525.1908)
      (321.6794 10396.9466) (379.7557 10396.9466) (402.1069 10525.1908) (424.4427 10525.1908) (446.7786 10610.687)
      (692.5038 10610.687) (719.313 10525.1908) (746.1221 10525.1908) (768.458 10396.9466) (826.5496 10396.9466)
      (848.8855 10525.1908) (871.2214 10525.1908) (893.5573 10610.687) (1139.2824 10610.687) (1166.0916 10525.1908)
      (1192.9008 10525.1908) (1215.2366 10396.9466) (1273.3282 10396.9466) (1295.6641 10525.1908) (1318.0 10525.1908)
      (1340.3359 10610.687) (1586.0611 10610.687) (1612.8702 10525.1908) (1639.6794 10525.1908) (1662.0153 10396.9466)
      (1720.1069 10396.9466) (1742.4427 10525.1908) (1764.7786 10525.1908) (1787.1145 10610.687) (2032.855 10610.687)
      (2059.6489 10525.1908) (2086.458 10525.1908) (2108.7939 10396.9466) (2166.8855 10396.9466) (2189.2214 10525.1908)
      (2211.5573 10525.1908) (2233.8931 10610.687) (2479.6336 10610.687) (2506.4275 10525.1908) (2533.2366 10525.1908)
      (2555.5725 10396.9466) (2613.6641 10396.9466) (2636.0 10525.1908) (2658.3359 10525.1908) (2680.6718 10610.687)
      (2926.4122 10610.687) (2953.2214 10525.1908) (2980.0153 10525.1908) (3002.3664 10396.9466) (3060.4427 10396.9466)
      (3082.7786 10525.1908) (3105.1145 10525.1908) (3127.4504 10610.687) (3373.1908 10610.687) (3400.0 10525.1908)
      (3426.7939 10525.1908) (3449.145 10396.9466) (3507.2214 10396.9466) (3529.5573 10525.1908) (3551.8931 10525.1908)
      (3574.2443 10610.687) (3819.9695 10610.687) (3846.7786 10525.1908) (3873.5725 10525.1908) (3895.9237 10396.9466)
      (3954.0 10396.9466) (3976.3359 10525.1908) (3998.6718 10525.1908) (4021.0229 10610.687) (4266.7481 10610.687)
      (4293.5573 10525.1908) (4320.3664 10525.1908) (4342.7023 10396.9466) (4400.7786 10396.9466) (4423.1145 10525.1908)
      (4445.4504 10525.1908) (4467.8015 10610.687) (4713.5267 10610.687) (4740.3359 10525.1908) (4767.145 10525.1908)
      (4789.4809 10396.9466) (4847.5573 10396.9466) (4869.8931 10525.1908) (4892.2443 10525.1908) (4914.5802 10610.687)
      (5160.3053 10610.687) (5160.3053 10259.542)
    ))
    ; P0124 -- see feature_dimensions_mm.csv
    ("02_CORNICES" 0 (
      (5007.6336 10122.1374) (122.1374 10122.1374)
    ))
    ; P0125 -- see feature_dimensions_mm.csv
    ("02_CORNICES" 0 (
      (167.9389 9969.4656) (122.1374 9969.4656) (122.1374 10122.1374)
    ))
    ; P0126 -- see feature_dimensions_mm.csv
    ("02_CORNICES" 0 (
      (5007.6336 9969.4656) (167.9389 9969.4656)
    ))
    ; P0127 -- see feature_dimensions_mm.csv
    ("02_CORNICES" 0 (
      (183.2061 9923.6641) (167.9389 9923.6641) (167.9389 9969.4656)
    ))
    ; P0128 -- see feature_dimensions_mm.csv
    ("02_CORNICES" 0 (
      (167.9389 9969.4656) (167.9389 9984.7328) (5007.6336 9984.7328)
    ))
    ; P0129 -- see feature_dimensions_mm.csv
    ("02_CORNICES" 0 (
      (267.5725 9923.6641) (183.2061 9923.6641)
    ))
    ; P0130 -- see feature_dimensions_mm.csv
    ("02_CORNICES" 0 (
      (183.2061 9603.0534) (183.2061 9923.6641)
    ))
    ; P0131 -- see feature_dimensions_mm.csv
    ("02_CORNICES" 0 (
      (183.2061 9923.6641) (183.2061 9938.9313) (267.5725 9938.9313)
    ))
    ; P0132 -- see feature_dimensions_mm.csv
    ("02_CORNICES" 0 (
      (267.5725 9603.0534) (183.2061 9603.0534)
    ))
    ; P0133 -- see feature_dimensions_mm.csv
    ("02_CORNICES" 0 (
      (183.2061 9572.5191) (183.2061 9587.7863) (183.2061 9603.0534)
    ))
    ; P0134 -- see feature_dimensions_mm.csv
    ("02_CORNICES" 0 (
      (4992.3664 9557.2519) (4885.4962 9557.2519) (4534.3511 9557.2519) (4213.7405 9557.2519) (3862.5954 9557.2519)
      (3541.9847 9557.2519) (3190.8397 9557.2519) (2870.229 9557.2519) (2519.084 9557.2519) (2198.4733 9557.2519)
      (1847.3282 9557.2519) (1526.7176 9557.2519) (1175.5725 9557.2519) (854.9618 9557.2519) (503.8168 9557.2519)
      (183.2061 9557.2519)
    ))
    ; P0135 -- see feature_dimensions_mm.csv
    ("02_CORNICES" 0 (
      (267.5725 9938.9313) (351.9542 9938.9313)
    ))
    ; P0136 -- see feature_dimensions_mm.csv
    ("02_CORNICES" 0 (
      (267.5725 9938.9313) (267.5725 9923.6641)
    ))
    ; P0137 -- see feature_dimensions_mm.csv
    ("02_CORNICES" 0 (
      (351.9542 9923.6641) (267.5725 9923.6641)
    ))
    ; P0138 -- see feature_dimensions_mm.csv
    ("02_CORNICES" 0 (
      (267.5725 9923.6641) (267.5725 9603.0534)
    ))
    ; P0139 -- see feature_dimensions_mm.csv
    ("02_CORNICES" 0 (
      (351.9542 9603.0534) (267.5725 9603.0534)
    ))
    ; P0140 -- see feature_dimensions_mm.csv
    ("02_CORNICES" 0 (
      (351.9542 9938.9313) (436.3206 9938.9313)
    ))
    ; P0141 -- see feature_dimensions_mm.csv
    ("02_CORNICES" 0 (
      (351.9542 9938.9313) (351.9542 9923.6641)
    ))
    ; P0142 -- see feature_dimensions_mm.csv
    ("02_CORNICES" 0 (
      (436.3206 9923.6641) (351.9542 9923.6641)
    ))
    ; P0143 -- see feature_dimensions_mm.csv
    ("02_CORNICES" 0 (
      (351.9542 9923.6641) (351.9542 9603.0534)
    ))
    ; P0144 -- see feature_dimensions_mm.csv
    ("02_CORNICES" 0 (
      (436.3206 9603.0534) (351.9542 9603.0534)
    ))
    ; P0145 -- see feature_dimensions_mm.csv
    ("02_CORNICES" 0 (
      (436.3206 9938.9313) (520.687 9938.9313)
    ))
    ; P0146 -- see feature_dimensions_mm.csv
    ("02_CORNICES" 0 (
      (436.3206 9938.9313) (436.3206 9923.6641)
    ))
    ; P0147 -- see feature_dimensions_mm.csv
    ("02_CORNICES" 0 (
      (520.687 9923.6641) (436.3206 9923.6641)
    ))
    ; P0148 -- see feature_dimensions_mm.csv
    ("02_CORNICES" 0 (
      (436.3206 9923.6641) (436.3206 9603.0534)
    ))
    ; P0149 -- see feature_dimensions_mm.csv
    ("02_CORNICES" 0 (
      (520.687 9603.0534) (436.3206 9603.0534)
    ))
    ; P0150 -- see feature_dimensions_mm.csv
    ("02_CORNICES" 0 (
      (520.687 9938.9313) (605.0687 9938.9313)
    ))
    ; P0151 -- see feature_dimensions_mm.csv
    ("02_CORNICES" 0 (
      (520.687 9938.9313) (520.687 9923.6641)
    ))
    ; P0152 -- see feature_dimensions_mm.csv
    ("02_CORNICES" 0 (
      (605.0687 9923.6641) (520.687 9923.6641)
    ))
    ; P0153 -- see feature_dimensions_mm.csv
    ("02_CORNICES" 0 (
      (520.687 9923.6641) (520.687 9603.0534)
    ))
    ; P0154 -- see feature_dimensions_mm.csv
    ("02_CORNICES" 0 (
      (605.0687 9603.0534) (520.687 9603.0534)
    ))
    ; P0155 -- see feature_dimensions_mm.csv
    ("02_CORNICES" 0 (
      (605.0687 9938.9313) (689.4351 9938.9313)
    ))
    ; P0156 -- see feature_dimensions_mm.csv
    ("02_CORNICES" 0 (
      (605.0687 9938.9313) (605.0687 9923.6641)
    ))
    ; P0157 -- see feature_dimensions_mm.csv
    ("02_CORNICES" 0 (
      (689.4351 9923.6641) (605.0687 9923.6641)
    ))
    ; P0158 -- see feature_dimensions_mm.csv
    ("02_CORNICES" 0 (
      (605.0687 9923.6641) (605.0687 9603.0534)
    ))
    ; P0159 -- see feature_dimensions_mm.csv
    ("02_CORNICES" 0 (
      (689.4351 9603.0534) (605.0687 9603.0534)
    ))
    ; P0160 -- see feature_dimensions_mm.csv
    ("02_CORNICES" 0 (
      (689.4351 9938.9313) (773.8015 9938.9313)
    ))
    ; P0161 -- see feature_dimensions_mm.csv
    ("02_CORNICES" 0 (
      (689.4351 9938.9313) (689.4351 9923.6641)
    ))
    ; P0162 -- see feature_dimensions_mm.csv
    ("02_CORNICES" 0 (
      (773.8015 9923.6641) (689.4351 9923.6641)
    ))
    ; P0163 -- see feature_dimensions_mm.csv
    ("02_CORNICES" 0 (
      (689.4351 9923.6641) (689.4351 9603.0534)
    ))
    ; P0164 -- see feature_dimensions_mm.csv
    ("02_CORNICES" 0 (
      (773.8015 9603.0534) (689.4351 9603.0534)
    ))
    ; P0165 -- see feature_dimensions_mm.csv
    ("02_CORNICES" 0 (
      (773.8015 9938.9313) (858.1832 9938.9313)
    ))
    ; P0166 -- see feature_dimensions_mm.csv
    ("02_CORNICES" 0 (
      (773.8015 9938.9313) (773.8015 9923.6641)
    ))
    ; P0167 -- see feature_dimensions_mm.csv
    ("02_CORNICES" 0 (
      (858.1832 9923.6641) (773.8015 9923.6641)
    ))
    ; P0168 -- see feature_dimensions_mm.csv
    ("02_CORNICES" 0 (
      (773.8015 9923.6641) (773.8015 9603.0534)
    ))
    ; P0169 -- see feature_dimensions_mm.csv
    ("02_CORNICES" 0 (
      (858.1832 9603.0534) (773.8015 9603.0534)
    ))
    ; P0170 -- see feature_dimensions_mm.csv
    ("02_CORNICES" 0 (
      (824.4275 3379.1298) (793.8931 3419.8473)
    ))
    ; P0171 -- see feature_dimensions_mm.csv
    ("02_CORNICES" 0 (
      (5137.4046 3389.313) (5068.7023 3297.7099) (885.4962 3297.7099) (824.4275 3379.1298)
    ))
    ; P0172 -- see feature_dimensions_mm.csv
    ("02_CORNICES" 0 (
      (5137.4046 3389.313) (5145.0382 3389.313) (5145.0382 3282.4427) (824.4275 3282.4427) (824.4275 3379.1298)
    ))
    ; P0173 -- see feature_dimensions_mm.csv
    ("02_CORNICES" 0 (
      (824.4275 3379.1298) (824.4275 3389.313) (5137.4046 3389.313)
    ))
    ; P0174 -- see feature_dimensions_mm.csv
    ("02_CORNICES" 0 (
      (839.6947 3633.5878) (854.9618 3633.5878)
    ))
    ; P0175 -- see feature_dimensions_mm.csv
    ("02_CORNICES" 0 (
      (854.9618 3633.5878) (931.2977 3633.5878)
    ))
    ; P0176 -- see feature_dimensions_mm.csv
    ("02_CORNICES" 0 (
      (5114.5038 3633.5878) (5114.5038 3618.3206) (854.9618 3618.3206) (854.9618 3633.5878)
    ))
    ; P0177 -- see feature_dimensions_mm.csv
    ("02_CORNICES" 0 (
      (854.9618 3633.5878) (854.9618 3679.3893) (931.2977 3679.3893)
    ))
    ; P0178 -- see feature_dimensions_mm.csv
    ("02_CORNICES" 0 (
      (858.1832 9938.9313) (942.5496 9938.9313)
    ))
    ; P0179 -- see feature_dimensions_mm.csv
    ("02_CORNICES" 0 (
      (858.1832 9938.9313) (858.1832 9923.6641)
    ))
    ; P0180 -- see feature_dimensions_mm.csv
    ("02_CORNICES" 0 (
      (942.5496 9923.6641) (858.1832 9923.6641)
    ))
    ; P0181 -- see feature_dimensions_mm.csv
    ("02_CORNICES" 0 (
      (858.1832 9923.6641) (858.1832 9603.0534)
    ))
    ; P0182 -- see feature_dimensions_mm.csv
    ("02_CORNICES" 0 (
      (942.5496 9603.0534) (858.1832 9603.0534)
    ))
    ; P0183 -- see feature_dimensions_mm.csv
    ("02_CORNICES" 0 (
      (931.2977 3679.3893) (961.8321 3679.3893) (1358.7786 3679.3893) (1389.313 3679.3893)
    ))
    ; P0184 -- see feature_dimensions_mm.csv
    ("02_CORNICES" 0 (
      (931.2977 3679.3893) (931.2977 3633.5878)
    ))
    ; P0185 -- see feature_dimensions_mm.csv
    ("02_CORNICES" 0 (
      (1389.313 3679.3893) (1389.313 3740.458) (1358.7786 3740.458) (961.8321 3740.458) (931.2977 3740.458)
      (931.2977 3709.9237) (931.2977 3679.3893)
    ))
    ; P0186 -- see feature_dimensions_mm.csv
    ("02_CORNICES" 0 (
      (931.2977 3633.5878) (961.8321 3633.5878) (1358.7786 3633.5878) (1389.313 3633.5878)
    ))
    ; P0187 -- see feature_dimensions_mm.csv
    ("02_CORNICES" 0 (
      (942.5496 9938.9313) (1026.916 9938.9313)
    ))
    ; P0188 -- see feature_dimensions_mm.csv
    ("02_CORNICES" 0 (
      (942.5496 9938.9313) (942.5496 9923.6641)
    ))
    ; P0189 -- see feature_dimensions_mm.csv
    ("02_CORNICES" 0 (
      (1026.916 9923.6641) (942.5496 9923.6641)
    ))
    ; P0190 -- see feature_dimensions_mm.csv
    ("02_CORNICES" 0 (
      (942.5496 9923.6641) (942.5496 9603.0534)
    ))
    ; P0191 -- see feature_dimensions_mm.csv
    ("02_CORNICES" 0 (
      (1026.916 9603.0534) (942.5496 9603.0534)
    ))
    ; P0192 -- see feature_dimensions_mm.csv
    ("02_CORNICES" 0 (
      (1031.1756 6656.4885) (961.8321 6656.4885) (946.5649 6656.4885)
    ))
    ; P0193 -- see feature_dimensions_mm.csv
    ("02_CORNICES" 0 (
      (961.8321 6564.8855) (946.5649 6564.8855) (946.5649 6656.4885)
    ))
    ; P0194 -- see feature_dimensions_mm.csv
    ("02_CORNICES" 0 (
      (946.5649 6656.4885) (946.5649 6885.4962) (946.5649 6977.0992) (961.8321 6977.0992) (1031.1756 6977.0992)
    ))
    ; P0195 -- see feature_dimensions_mm.csv
    ("02_CORNICES" 0 (
      (1021.5267 8076.3359) (1046.3511 7996.9466) (1071.1908 7996.9466) (1091.8779 7877.8626) (1145.6947 7877.8626)
      (1166.3817 7996.9466) (1187.084 7996.9466) (1207.771 8076.3359)
    ))
    ; P0196 -- see feature_dimensions_mm.csv
    ("02_CORNICES" 0 (
      (1026.916 9938.9313) (1111.2824 9938.9313)
    ))
    ; P0197 -- see feature_dimensions_mm.csv
    ("02_CORNICES" 0 (
      (1026.916 9938.9313) (1026.916 9923.6641)
    ))
    ; P0198 -- see feature_dimensions_mm.csv
    ("02_CORNICES" 0 (
      (1111.2824 9923.6641) (1026.916 9923.6641)
    ))
    ; P0199 -- see feature_dimensions_mm.csv
    ("02_CORNICES" 0 (
      (1026.916 9923.6641) (1026.916 9603.0534)
    ))
    ; P0200 -- see feature_dimensions_mm.csv
    ("02_CORNICES" 0 (
      (1111.2824 9603.0534) (1026.916 9603.0534)
    ))
    ; P0201 -- see feature_dimensions_mm.csv
    ("02_CORNICES" 0 (
      (1031.1756 6977.0992) (1115.771 6977.0992)
    ))
    ; P0202 -- see feature_dimensions_mm.csv
    ("02_CORNICES" 0 (
      (1031.1756 6977.0992) (1031.1756 6656.4885)
    ))
    ; P0203 -- see feature_dimensions_mm.csv
    ("02_CORNICES" 0 (
      (1115.771 6656.4885) (1031.1756 6656.4885)
    ))
    ; P0204 -- see feature_dimensions_mm.csv
    ("02_CORNICES" 0 (
      (1111.2824 9938.9313) (1195.6641 9938.9313)
    ))
    ; P0205 -- see feature_dimensions_mm.csv
    ("02_CORNICES" 0 (
      (1111.2824 9938.9313) (1111.2824 9923.6641)
    ))
    ; P0206 -- see feature_dimensions_mm.csv
    ("02_CORNICES" 0 (
      (1195.6641 9923.6641) (1111.2824 9923.6641)
    ))
    ; P0207 -- see feature_dimensions_mm.csv
    ("02_CORNICES" 0 (
      (1111.2824 9923.6641) (1111.2824 9603.0534)
    ))
    ; P0208 -- see feature_dimensions_mm.csv
    ("02_CORNICES" 0 (
      (1195.6641 9603.0534) (1111.2824 9603.0534)
    ))
    ; P0209 -- see feature_dimensions_mm.csv
    ("02_CORNICES" 0 (
      (1115.771 6977.0992) (1200.3817 6977.0992)
    ))
    ; P0210 -- see feature_dimensions_mm.csv
    ("02_CORNICES" 0 (
      (1115.771 6977.0992) (1115.771 6656.4885)
    ))
    ; P0211 -- see feature_dimensions_mm.csv
    ("02_CORNICES" 0 (
      (1200.3817 6656.4885) (1115.771 6656.4885)
    ))
    ; P0212 -- see feature_dimensions_mm.csv
    ("02_CORNICES" 0 (
      (1195.6641 9938.9313) (1280.0305 9938.9313)
    ))
    ; P0213 -- see feature_dimensions_mm.csv
    ("02_CORNICES" 0 (
      (1195.6641 9938.9313) (1195.6641 9923.6641)
    ))
    ; P0214 -- see feature_dimensions_mm.csv
    ("02_CORNICES" 0 (
      (1280.0305 9923.6641) (1195.6641 9923.6641)
    ))
    ; P0215 -- see feature_dimensions_mm.csv
    ("02_CORNICES" 0 (
      (1195.6641 9923.6641) (1195.6641 9603.0534)
    ))
    ; P0216 -- see feature_dimensions_mm.csv
    ("02_CORNICES" 0 (
      (1280.0305 9603.0534) (1195.6641 9603.0534)
    ))
    ; P0217 -- see feature_dimensions_mm.csv
    ("02_CORNICES" 0 (
      (1200.3817 6977.0992) (1284.9924 6977.0992)
    ))
    ; P0218 -- see feature_dimensions_mm.csv
    ("02_CORNICES" 0 (
      (1200.3817 6977.0992) (1200.3817 6656.4885)
    ))
    ; P0219 -- see feature_dimensions_mm.csv
    ("02_CORNICES" 0 (
      (1284.9924 6656.4885) (1200.3817 6656.4885)
    ))
    ; P0220 -- see feature_dimensions_mm.csv
    ("02_CORNICES" 0 (
      (1236.6412 2061.0687) (1684.4122 2061.0687)
    ))
    ; P0221 -- see feature_dimensions_mm.csv
    ("02_CORNICES" 0 (
      (1280.0305 9938.9313) (1364.3969 9938.9313)
    ))
    ; P0222 -- see feature_dimensions_mm.csv
    ("02_CORNICES" 0 (
      (1280.0305 9938.9313) (1280.0305 9923.6641)
    ))
    ; P0223 -- see feature_dimensions_mm.csv
    ("02_CORNICES" 0 (
      (1364.3969 9923.6641) (1280.0305 9923.6641)
    ))
    ; P0224 -- see feature_dimensions_mm.csv
    ("02_CORNICES" 0 (
      (1280.0305 9923.6641) (1280.0305 9603.0534)
    ))
    ; P0225 -- see feature_dimensions_mm.csv
    ("02_CORNICES" 0 (
      (1364.3969 9603.0534) (1280.0305 9603.0534)
    ))
    ; P0226 -- see feature_dimensions_mm.csv
    ("02_CORNICES" 0 (
      (1284.9924 6977.0992) (1369.5878 6977.0992)
    ))
    ; P0227 -- see feature_dimensions_mm.csv
    ("02_CORNICES" 0 (
      (1284.9924 6977.0992) (1284.9924 6656.4885)
    ))
    ; P0228 -- see feature_dimensions_mm.csv
    ("02_CORNICES" 0 (
      (1369.5878 6656.4885) (1284.9924 6656.4885)
    ))
    ; P0229 -- see feature_dimensions_mm.csv
    ("02_CORNICES" 0 (
      (1664.1221 1862.5954) (1435.1145 1862.5954) (1404.5802 1862.5954) (1343.5115 1969.4656)
    ))
    ; P0230 -- see feature_dimensions_mm.csv
    ("02_CORNICES" 0 (
      (1364.3969 9938.9313) (1448.7786 9938.9313)
    ))
    ; P0231 -- see feature_dimensions_mm.csv
    ("02_CORNICES" 0 (
      (1364.3969 9938.9313) (1364.3969 9923.6641)
    ))
    ; P0232 -- see feature_dimensions_mm.csv
    ("02_CORNICES" 0 (
      (1448.7786 9923.6641) (1364.3969 9923.6641)
    ))
    ; P0233 -- see feature_dimensions_mm.csv
    ("02_CORNICES" 0 (
      (1364.3969 9923.6641) (1364.3969 9603.0534)
    ))
    ; P0234 -- see feature_dimensions_mm.csv
    ("02_CORNICES" 0 (
      (1448.7786 9603.0534) (1364.3969 9603.0534)
    ))
    ; P0235 -- see feature_dimensions_mm.csv
    ("02_CORNICES" 0 (
      (1369.5878 6977.0992) (1454.1985 6977.0992)
    ))
    ; P0236 -- see feature_dimensions_mm.csv
    ("02_CORNICES" 0 (
      (1369.5878 6977.0992) (1369.5878 6656.4885)
    ))
    ; P0237 -- see feature_dimensions_mm.csv
    ("02_CORNICES" 0 (
      (1454.1985 6656.4885) (1369.5878 6656.4885)
    ))
    ; P0238 -- see feature_dimensions_mm.csv
    ("02_CORNICES" 0 (
      (1389.313 3679.3893) (1969.4656 3679.3893) (3984.7328 3679.3893) (4564.8855 3679.3893)
    ))
    ; P0239 -- see feature_dimensions_mm.csv
    ("02_CORNICES" 0 (
      (1389.313 3633.5878) (1389.313 3679.3893)
    ))
    ; P0240 -- see feature_dimensions_mm.csv
    ("02_CORNICES" 0 (
      (1389.313 3633.5878) (1969.4656 3633.5878)
    ))
    ; P0241 -- see feature_dimensions_mm.csv
    ("02_CORNICES" 0 (
      (1435.4046 8076.3359) (1460.2443 7996.9466) (1485.0687 7996.9466) (1505.7557 7877.8626) (1559.5725 7877.8626)
      (1580.2595 7996.9466) (1600.9618 7996.9466) (1621.6489 8076.3359)
    ))
    ; P0242 -- see feature_dimensions_mm.csv
    ("02_CORNICES" 0 (
      (1448.7786 9938.9313) (1533.145 9938.9313)
    ))
    ; P0243 -- see feature_dimensions_mm.csv
    ("02_CORNICES" 0 (
      (1448.7786 9938.9313) (1448.7786 9923.6641)
    ))
    ; P0244 -- see feature_dimensions_mm.csv
    ("02_CORNICES" 0 (
      (1533.145 9923.6641) (1448.7786 9923.6641)
    ))
    ; P0245 -- see feature_dimensions_mm.csv
    ("02_CORNICES" 0 (
      (1448.7786 9923.6641) (1448.7786 9603.0534)
    ))
    ; P0246 -- see feature_dimensions_mm.csv
    ("02_CORNICES" 0 (
      (1533.145 9603.0534) (1448.7786 9603.0534)
    ))
    ; P0247 -- see feature_dimensions_mm.csv
    ("02_CORNICES" 0 (
      (1454.1985 6977.0992) (1538.8092 6977.0992)
    ))
    ; P0248 -- see feature_dimensions_mm.csv
    ("02_CORNICES" 0 (
      (1454.1985 6977.0992) (1454.1985 6656.4885)
    ))
    ; P0249 -- see feature_dimensions_mm.csv
    ("02_CORNICES" 0 (
      (1538.8092 6656.4885) (1454.1985 6656.4885)
    ))
    ; P0250 -- see feature_dimensions_mm.csv
    ("02_CORNICES" 0 (
      (1533.145 9938.9313) (1617.5115 9938.9313)
    ))
    ; P0251 -- see feature_dimensions_mm.csv
    ("02_CORNICES" 0 (
      (1533.145 9938.9313) (1533.145 9923.6641)
    ))
    ; P0252 -- see feature_dimensions_mm.csv
    ("02_CORNICES" 0 (
      (1617.5115 9923.6641) (1533.145 9923.6641)
    ))
    ; P0253 -- see feature_dimensions_mm.csv
    ("02_CORNICES" 0 (
      (1533.145 9923.6641) (1533.145 9603.0534)
    ))
    ; P0254 -- see feature_dimensions_mm.csv
    ("02_CORNICES" 0 (
      (1617.5115 9603.0534) (1533.145 9603.0534)
    ))
    ; P0255 -- see feature_dimensions_mm.csv
    ("02_CORNICES" 0 (
      (1538.8092 6977.0992) (1623.4046 6977.0992)
    ))
    ; P0256 -- see feature_dimensions_mm.csv
    ("02_CORNICES" 0 (
      (1538.8092 6977.0992) (1538.8092 6656.4885)
    ))
    ; P0257 -- see feature_dimensions_mm.csv
    ("02_CORNICES" 0 (
      (1623.4046 6656.4885) (1538.8092 6656.4885)
    ))
    ; P0258 -- see feature_dimensions_mm.csv
    ("02_CORNICES" 0 (
      (1617.5115 9938.9313) (1701.8931 9938.9313)
    ))
    ; P0259 -- see feature_dimensions_mm.csv
    ("02_CORNICES" 0 (
      (1617.5115 9938.9313) (1617.5115 9923.6641)
    ))
    ; P0260 -- see feature_dimensions_mm.csv
    ("02_CORNICES" 0 (
      (1701.8931 9923.6641) (1617.5115 9923.6641)
    ))
    ; P0261 -- see feature_dimensions_mm.csv
    ("02_CORNICES" 0 (
      (1617.5115 9923.6641) (1617.5115 9603.0534)
    ))
    ; P0262 -- see feature_dimensions_mm.csv
    ("02_CORNICES" 0 (
      (1701.8931 9603.0534) (1617.5115 9603.0534)
    ))
    ; P0263 -- see feature_dimensions_mm.csv
    ("02_CORNICES" 0 (
      (1623.4046 6977.0992) (1708.0153 6977.0992)
    ))
    ; P0264 -- see feature_dimensions_mm.csv
    ("02_CORNICES" 0 (
      (1623.4046 6977.0992) (1623.4046 6656.4885)
    ))
    ; P0265 -- see feature_dimensions_mm.csv
    ("02_CORNICES" 0 (
      (1708.0153 6656.4885) (1623.4046 6656.4885)
    ))
    ; P0266 -- see feature_dimensions_mm.csv
    ("02_CORNICES" 0 (
      (1701.8931 9938.9313) (1786.2595 9938.9313)
    ))
    ; P0267 -- see feature_dimensions_mm.csv
    ("02_CORNICES" 0 (
      (1701.8931 9938.9313) (1701.8931 9923.6641)
    ))
    ; P0268 -- see feature_dimensions_mm.csv
    ("02_CORNICES" 0 (
      (1786.2595 9923.6641) (1701.8931 9923.6641)
    ))
    ; P0269 -- see feature_dimensions_mm.csv
    ("02_CORNICES" 0 (
      (1701.8931 9923.6641) (1701.8931 9603.0534)
    ))
    ; P0270 -- see feature_dimensions_mm.csv
    ("02_CORNICES" 0 (
      (1786.2595 9603.0534) (1701.8931 9603.0534)
    ))
    ; P0271 -- see feature_dimensions_mm.csv
    ("02_CORNICES" 0 (
      (1708.0153 6977.0992) (1792.626 6977.0992)
    ))
    ; P0272 -- see feature_dimensions_mm.csv
    ("02_CORNICES" 0 (
      (1708.0153 6977.0992) (1708.0153 6656.4885)
    ))
    ; P0273 -- see feature_dimensions_mm.csv
    ("02_CORNICES" 0 (
      (1792.626 6656.4885) (1708.0153 6656.4885)
    ))
    ; P0274 -- see feature_dimensions_mm.csv
    ("02_CORNICES" 0 (
      (1786.2595 9938.9313) (1870.626 9938.9313)
    ))
    ; P0275 -- see feature_dimensions_mm.csv
    ("02_CORNICES" 0 (
      (1786.2595 9938.9313) (1786.2595 9923.6641)
    ))
    ; P0276 -- see feature_dimensions_mm.csv
    ("02_CORNICES" 0 (
      (1870.626 9923.6641) (1786.2595 9923.6641)
    ))
    ; P0277 -- see feature_dimensions_mm.csv
    ("02_CORNICES" 0 (
      (1786.2595 9923.6641) (1786.2595 9603.0534)
    ))
    ; P0278 -- see feature_dimensions_mm.csv
    ("02_CORNICES" 0 (
      (1870.626 9603.0534) (1786.2595 9603.0534)
    ))
    ; P0279 -- see feature_dimensions_mm.csv
    ("02_CORNICES" 0 (
      (1792.626 6977.0992) (1877.2214 6977.0992)
    ))
    ; P0280 -- see feature_dimensions_mm.csv
    ("02_CORNICES" 0 (
      (1792.626 6977.0992) (1792.626 6656.4885)
    ))
    ; P0281 -- see feature_dimensions_mm.csv
    ("02_CORNICES" 0 (
      (1877.2214 6656.4885) (1792.626 6656.4885)
    ))
    ; P0282 -- see feature_dimensions_mm.csv
    ("02_CORNICES" 0 (
      (1847.3282 8076.3359) (1849.2824 8076.3359) (1874.1221 7996.9466) (1898.9466 7996.9466) (1919.6336 7877.8626)
      (1973.4504 7877.8626) (1994.1374 7996.9466) (2014.8397 7996.9466) (2035.5267 8076.3359) (2198.4733 8076.3359)
      (2263.1603 8076.3359) (2288.0 7996.9466) (2312.8244 7996.9466) (2333.5267 7877.8626) (2387.3282 7877.8626)
      (2408.0153 7996.9466) (2428.7176 7996.9466) (2449.4046 8076.3359) (2519.084 8076.3359) (2677.0382 8076.3359)
      (2701.8779 7996.9466) (2726.7023 7996.9466) (2747.4046 7877.8626) (2801.2061 7877.8626) (2821.8931 7996.9466)
      (2842.5954 7996.9466) (2863.2824 8076.3359) (2870.229 8076.3359)
    ))
    ; P0283 -- see feature_dimensions_mm.csv
    ("02_CORNICES" 0 (
      (1870.626 9938.9313) (1955.0076 9938.9313)
    ))
    ; P0284 -- see feature_dimensions_mm.csv
    ("02_CORNICES" 0 (
      (1870.626 9938.9313) (1870.626 9923.6641)
    ))
    ; P0285 -- see feature_dimensions_mm.csv
    ("02_CORNICES" 0 (
      (1955.0076 9923.6641) (1870.626 9923.6641)
    ))
    ; P0286 -- see feature_dimensions_mm.csv
    ("02_CORNICES" 0 (
      (1870.626 9923.6641) (1870.626 9603.0534)
    ))
    ; P0287 -- see feature_dimensions_mm.csv
    ("02_CORNICES" 0 (
      (1955.0076 9603.0534) (1870.626 9603.0534)
    ))
    ; P0288 -- see feature_dimensions_mm.csv
    ("02_CORNICES" 0 (
      (1877.2214 6977.0992) (1961.8321 6977.0992)
    ))
    ; P0289 -- see feature_dimensions_mm.csv
    ("02_CORNICES" 0 (
      (1877.2214 6977.0992) (1877.2214 6656.4885)
    ))
    ; P0290 -- see feature_dimensions_mm.csv
    ("02_CORNICES" 0 (
      (1961.8321 6656.4885) (1877.2214 6656.4885)
    ))
    ; P0291 -- see feature_dimensions_mm.csv
    ("02_CORNICES" 0 (
      (1955.0076 9938.9313) (2039.374 9938.9313)
    ))
    ; P0292 -- see feature_dimensions_mm.csv
    ("02_CORNICES" 0 (
      (1955.0076 9938.9313) (1955.0076 9923.6641)
    ))
    ; P0293 -- see feature_dimensions_mm.csv
    ("02_CORNICES" 0 (
      (2039.374 9923.6641) (1955.0076 9923.6641)
    ))
    ; P0294 -- see feature_dimensions_mm.csv
    ("02_CORNICES" 0 (
      (1955.0076 9923.6641) (1955.0076 9603.0534)
    ))
    ; P0295 -- see feature_dimensions_mm.csv
    ("02_CORNICES" 0 (
      (2039.374 9603.0534) (1955.0076 9603.0534)
    ))
    ; P0296 -- see feature_dimensions_mm.csv
    ("02_CORNICES" 0 (
      (1961.8321 6977.0992) (2046.4427 6977.0992)
    ))
    ; P0297 -- see feature_dimensions_mm.csv
    ("02_CORNICES" 0 (
      (1961.8321 6977.0992) (1961.8321 6656.4885)
    ))
    ; P0298 -- see feature_dimensions_mm.csv
    ("02_CORNICES" 0 (
      (2046.4427 6656.4885) (1961.8321 6656.4885)
    ))
    ; P0299 -- see feature_dimensions_mm.csv
    ("02_CORNICES" 0 (
      (2039.374 9938.9313) (2123.7405 9938.9313)
    ))
    ; P0300 -- see feature_dimensions_mm.csv
    ("02_CORNICES" 0 (
      (2039.374 9938.9313) (2039.374 9923.6641)
    ))
    ; P0301 -- see feature_dimensions_mm.csv
    ("02_CORNICES" 0 (
      (2123.7405 9923.6641) (2039.374 9923.6641)
    ))
    ; P0302 -- see feature_dimensions_mm.csv
    ("02_CORNICES" 0 (
      (2039.374 9923.6641) (2039.374 9603.0534)
    ))
    ; P0303 -- see feature_dimensions_mm.csv
    ("02_CORNICES" 0 (
      (2123.7405 9603.0534) (2039.374 9603.0534)
    ))
    ; P0304 -- see feature_dimensions_mm.csv
    ("02_CORNICES" 0 (
      (2046.4427 6977.0992) (2131.0382 6977.0992)
    ))
    ; P0305 -- see feature_dimensions_mm.csv
    ("02_CORNICES" 0 (
      (2046.4427 6977.0992) (2046.4427 6656.4885)
    ))
    ; P0306 -- see feature_dimensions_mm.csv
    ("02_CORNICES" 0 (
      (2131.0382 6656.4885) (2046.4427 6656.4885)
    ))
    ; P0307 -- see feature_dimensions_mm.csv
    ("02_CORNICES" 0 (
      (2123.7405 9938.9313) (2208.1221 9938.9313)
    ))
    ; P0308 -- see feature_dimensions_mm.csv
    ("02_CORNICES" 0 (
      (2123.7405 9938.9313) (2123.7405 9923.6641)
    ))
    ; P0309 -- see feature_dimensions_mm.csv
    ("02_CORNICES" 0 (
      (2208.1221 9923.6641) (2123.7405 9923.6641)
    ))
    ; P0310 -- see feature_dimensions_mm.csv
    ("02_CORNICES" 0 (
      (2123.7405 9923.6641) (2123.7405 9603.0534)
    ))
    ; P0311 -- see feature_dimensions_mm.csv
    ("02_CORNICES" 0 (
      (2208.1221 9603.0534) (2123.7405 9603.0534)
    ))
    ; P0312 -- see feature_dimensions_mm.csv
    ("02_CORNICES" 0 (
      (2131.0382 6977.0992) (2215.6489 6977.0992)
    ))
    ; P0313 -- see feature_dimensions_mm.csv
    ("02_CORNICES" 0 (
      (2131.0382 6977.0992) (2131.0382 6656.4885)
    ))
    ; P0314 -- see feature_dimensions_mm.csv
    ("02_CORNICES" 0 (
      (2215.6489 6656.4885) (2131.0382 6656.4885)
    ))
    ; P0315 -- see feature_dimensions_mm.csv
    ("02_CORNICES" 0 (
      (2162.2595 2373.2977) (2150.1985 2433.2366) (2114.5038 2610.687) (2404.5802 2610.687) (2368.8855 2433.2366)
      (2356.8244 2373.2977)
    ))
    ; P0316 -- see feature_dimensions_mm.csv
    ("02_CORNICES" 0 (
      (2208.1221 9938.9313) (2292.4885 9938.9313)
    ))
    ; P0317 -- see feature_dimensions_mm.csv
    ("02_CORNICES" 0 (
      (2208.1221 9938.9313) (2208.1221 9923.6641)
    ))
    ; P0318 -- see feature_dimensions_mm.csv
    ("02_CORNICES" 0 (
      (2292.4885 9923.6641) (2208.1221 9923.6641)
    ))
    ; P0319 -- see feature_dimensions_mm.csv
    ("02_CORNICES" 0 (
      (2208.1221 9923.6641) (2208.1221 9603.0534)
    ))
    ; P0320 -- see feature_dimensions_mm.csv
    ("02_CORNICES" 0 (
      (2292.4885 9603.0534) (2208.1221 9603.0534)
    ))
    ; P0321 -- see feature_dimensions_mm.csv
    ("02_CORNICES" 0 (
      (2215.6489 6977.0992) (2300.2595 6977.0992)
    ))
    ; P0322 -- see feature_dimensions_mm.csv
    ("02_CORNICES" 0 (
      (2215.6489 6977.0992) (2215.6489 6656.4885)
    ))
    ; P0323 -- see feature_dimensions_mm.csv
    ("02_CORNICES" 0 (
      (2300.2595 6656.4885) (2215.6489 6656.4885)
    ))
    ; P0324 -- see feature_dimensions_mm.csv
    ("02_CORNICES" 0 (
      (2292.4885 9938.9313) (2376.855 9938.9313)
    ))
    ; P0325 -- see feature_dimensions_mm.csv
    ("02_CORNICES" 0 (
      (2292.4885 9938.9313) (2292.4885 9923.6641)
    ))
    ; P0326 -- see feature_dimensions_mm.csv
    ("02_CORNICES" 0 (
      (2376.855 9923.6641) (2292.4885 9923.6641)
    ))
    ; P0327 -- see feature_dimensions_mm.csv
    ("02_CORNICES" 0 (
      (2292.4885 9923.6641) (2292.4885 9603.0534)
    ))
    ; P0328 -- see feature_dimensions_mm.csv
    ("02_CORNICES" 0 (
      (2376.855 9603.0534) (2292.4885 9603.0534)
    ))
    ; P0329 -- see feature_dimensions_mm.csv
    ("02_CORNICES" 0 (
      (2300.2595 6977.0992) (2384.855 6977.0992)
    ))
    ; P0330 -- see feature_dimensions_mm.csv
    ("02_CORNICES" 0 (
      (2300.2595 6977.0992) (2300.2595 6656.4885)
    ))
    ; P0331 -- see feature_dimensions_mm.csv
    ("02_CORNICES" 0 (
      (2384.855 6656.4885) (2300.2595 6656.4885)
    ))
    ; P0332 -- see feature_dimensions_mm.csv
    ("02_CORNICES" 0 (
      (2376.855 9938.9313) (2461.2366 9938.9313)
    ))
    ; P0333 -- see feature_dimensions_mm.csv
    ("02_CORNICES" 0 (
      (2376.855 9938.9313) (2376.855 9923.6641)
    ))
    ; P0334 -- see feature_dimensions_mm.csv
    ("02_CORNICES" 0 (
      (2461.2366 9923.6641) (2376.855 9923.6641)
    ))
    ; P0335 -- see feature_dimensions_mm.csv
    ("02_CORNICES" 0 (
      (2376.855 9923.6641) (2376.855 9603.0534)
    ))
    ; P0336 -- see feature_dimensions_mm.csv
    ("02_CORNICES" 0 (
      (2461.2366 9603.0534) (2376.855 9603.0534)
    ))
    ; P0337 -- see feature_dimensions_mm.csv
    ("02_CORNICES" 0 (
      (2384.855 6977.0992) (2469.4656 6977.0992)
    ))
    ; P0338 -- see feature_dimensions_mm.csv
    ("02_CORNICES" 0 (
      (2384.855 6977.0992) (2384.855 6656.4885)
    ))
    ; P0339 -- see feature_dimensions_mm.csv
    ("02_CORNICES" 0 (
      (2469.4656 6656.4885) (2384.855 6656.4885)
    ))
    ; P0340 -- see feature_dimensions_mm.csv
    ("02_CORNICES" 0 (
      (2461.2366 9938.9313) (2545.6031 9938.9313)
    ))
    ; P0341 -- see feature_dimensions_mm.csv
    ("02_CORNICES" 0 (
      (2461.2366 9938.9313) (2461.2366 9923.6641)
    ))
    ; P0342 -- see feature_dimensions_mm.csv
    ("02_CORNICES" 0 (
      (2545.6031 9923.6641) (2461.2366 9923.6641)
    ))
    ; P0343 -- see feature_dimensions_mm.csv
    ("02_CORNICES" 0 (
      (2461.2366 9923.6641) (2461.2366 9603.0534)
    ))
    ; P0344 -- see feature_dimensions_mm.csv
    ("02_CORNICES" 0 (
      (2545.6031 9603.0534) (2461.2366 9603.0534)
    ))
    ; P0345 -- see feature_dimensions_mm.csv
    ("02_CORNICES" 0 (
      (2469.4656 6977.0992) (2554.0763 6977.0992)
    ))
    ; P0346 -- see feature_dimensions_mm.csv
    ("02_CORNICES" 0 (
      (2469.4656 6977.0992) (2469.4656 6656.4885)
    ))
    ; P0347 -- see feature_dimensions_mm.csv
    ("02_CORNICES" 0 (
      (2554.0763 6656.4885) (2469.4656 6656.4885)
    ))
    ; P0348 -- see feature_dimensions_mm.csv
    ("02_CORNICES" 0 (
      (2545.6031 9938.9313) (2629.9695 9938.9313)
    ))
    ; P0349 -- see feature_dimensions_mm.csv
    ("02_CORNICES" 0 (
      (2545.6031 9938.9313) (2545.6031 9923.6641)
    ))
    ; P0350 -- see feature_dimensions_mm.csv
    ("02_CORNICES" 0 (
      (2629.9695 9923.6641) (2545.6031 9923.6641)
    ))
    ; P0351 -- see feature_dimensions_mm.csv
    ("02_CORNICES" 0 (
      (2545.6031 9923.6641) (2545.6031 9603.0534)
    ))
    ; P0352 -- see feature_dimensions_mm.csv
    ("02_CORNICES" 0 (
      (2629.9695 9603.0534) (2545.6031 9603.0534)
    ))
    ; P0353 -- see feature_dimensions_mm.csv
    ("02_CORNICES" 0 (
      (2554.0763 6977.0992) (2638.6718 6977.0992)
    ))
    ; P0354 -- see feature_dimensions_mm.csv
    ("02_CORNICES" 0 (
      (2554.0763 6977.0992) (2554.0763 6656.4885)
    ))
    ; P0355 -- see feature_dimensions_mm.csv
    ("02_CORNICES" 0 (
      (2638.6718 6656.4885) (2554.0763 6656.4885)
    ))
    ; P0356 -- see feature_dimensions_mm.csv
    ("02_CORNICES" 0 (
      (2629.9695 9938.9313) (2714.3359 9938.9313)
    ))
    ; P0357 -- see feature_dimensions_mm.csv
    ("02_CORNICES" 0 (
      (2629.9695 9938.9313) (2629.9695 9923.6641)
    ))
    ; P0358 -- see feature_dimensions_mm.csv
    ("02_CORNICES" 0 (
      (2714.3359 9923.6641) (2629.9695 9923.6641)
    ))
    ; P0359 -- see feature_dimensions_mm.csv
    ("02_CORNICES" 0 (
      (2629.9695 9923.6641) (2629.9695 9603.0534)
    ))
    ; P0360 -- see feature_dimensions_mm.csv
    ("02_CORNICES" 0 (
      (2714.3359 9603.0534) (2629.9695 9603.0534)
    ))
    ; P0361 -- see feature_dimensions_mm.csv
    ("02_CORNICES" 0 (
      (2638.6718 6977.0992) (2723.2824 6977.0992)
    ))
    ; P0362 -- see feature_dimensions_mm.csv
    ("02_CORNICES" 0 (
      (2638.6718 6977.0992) (2638.6718 6656.4885)
    ))
    ; P0363 -- see feature_dimensions_mm.csv
    ("02_CORNICES" 0 (
      (2723.2824 6656.4885) (2638.6718 6656.4885)
    ))
    ; P0364 -- see feature_dimensions_mm.csv
    ("02_CORNICES" 0 (
      (2714.3359 9938.9313) (2798.7176 9938.9313)
    ))
    ; P0365 -- see feature_dimensions_mm.csv
    ("02_CORNICES" 0 (
      (2714.3359 9938.9313) (2714.3359 9923.6641)
    ))
    ; P0366 -- see feature_dimensions_mm.csv
    ("02_CORNICES" 0 (
      (2798.7176 9923.6641) (2714.3359 9923.6641)
    ))
    ; P0367 -- see feature_dimensions_mm.csv
    ("02_CORNICES" 0 (
      (2714.3359 9923.6641) (2714.3359 9603.0534)
    ))
    ; P0368 -- see feature_dimensions_mm.csv
    ("02_CORNICES" 0 (
      (2798.7176 9603.0534) (2714.3359 9603.0534)
    ))
    ; P0369 -- see feature_dimensions_mm.csv
    ("02_CORNICES" 0 (
      (2723.2824 6977.0992) (2807.8931 6977.0992)
    ))
    ; P0370 -- see feature_dimensions_mm.csv
    ("02_CORNICES" 0 (
      (2723.2824 6977.0992) (2723.2824 6656.4885)
    ))
    ; P0371 -- see feature_dimensions_mm.csv
    ("02_CORNICES" 0 (
      (2807.8931 6656.4885) (2723.2824 6656.4885)
    ))
    ; P0372 -- see feature_dimensions_mm.csv
    ("02_CORNICES" 0 (
      (2798.7176 9938.9313) (2883.084 9938.9313)
    ))
    ; P0373 -- see feature_dimensions_mm.csv
    ("02_CORNICES" 0 (
      (2798.7176 9938.9313) (2798.7176 9923.6641)
    ))
    ; P0374 -- see feature_dimensions_mm.csv
    ("02_CORNICES" 0 (
      (2883.084 9923.6641) (2798.7176 9923.6641)
    ))
    ; P0375 -- see feature_dimensions_mm.csv
    ("02_CORNICES" 0 (
      (2798.7176 9923.6641) (2798.7176 9603.0534)
    ))
    ; P0376 -- see feature_dimensions_mm.csv
    ("02_CORNICES" 0 (
      (2883.084 9603.0534) (2798.7176 9603.0534)
    ))
    ; P0377 -- see feature_dimensions_mm.csv
    ("02_CORNICES" 0 (
      (2807.8931 6977.0992) (2892.4885 6977.0992)
    ))
    ; P0378 -- see feature_dimensions_mm.csv
    ("02_CORNICES" 0 (
      (2807.8931 6977.0992) (2807.8931 6656.4885)
    ))
    ; P0379 -- see feature_dimensions_mm.csv
    ("02_CORNICES" 0 (
      (2892.4885 6656.4885) (2807.8931 6656.4885)
    ))
    ; P0380 -- see feature_dimensions_mm.csv
    ("02_CORNICES" 0 (
      (2861.2061 1990.2748) (2854.7481 1995.8321)
    ))
    ; P0381 -- see feature_dimensions_mm.csv
    ("02_CORNICES" 0 (
      (3056.4885 5938.9313) (3032.0611 5938.9313) (3004.5802 5938.9313) (2977.0992 5938.9313) (2949.6183 5938.9313)
      (2922.1374 5938.9313) (2897.7099 5938.9313) (2863.6794 5938.9313) (2824.4275 5938.9313) (2857.4504 5782.9924)
      (2879.3893 5679.3893)
    ))
    ; P0382 -- see feature_dimensions_mm.csv
    ("02_CORNICES" 0 (
      (2883.084 9938.9313) (2967.4504 9938.9313)
    ))
    ; P0383 -- see feature_dimensions_mm.csv
    ("02_CORNICES" 0 (
      (2883.084 9938.9313) (2883.084 9923.6641)
    ))
    ; P0384 -- see feature_dimensions_mm.csv
    ("02_CORNICES" 0 (
      (2967.4504 9923.6641) (2883.084 9923.6641)
    ))
    ; P0385 -- see feature_dimensions_mm.csv
    ("02_CORNICES" 0 (
      (2883.084 9923.6641) (2883.084 9603.0534)
    ))
    ; P0386 -- see feature_dimensions_mm.csv
    ("02_CORNICES" 0 (
      (2967.4504 9603.0534) (2883.084 9603.0534)
    ))
    ; P0387 -- see feature_dimensions_mm.csv
    ("02_CORNICES" 0 (
      (3114.5038 1862.5954) (2946.5649 1862.5954) (2885.4962 1969.4656)
    ))
    ; P0388 -- see feature_dimensions_mm.csv
    ("02_CORNICES" 0 (
      (2892.4885 6977.0992) (2977.0992 6977.0992)
    ))
    ; P0389 -- see feature_dimensions_mm.csv
    ("02_CORNICES" 0 (
      (2892.4885 6977.0992) (2892.4885 6656.4885)
    ))
    ; P0390 -- see feature_dimensions_mm.csv
    ("02_CORNICES" 0 (
      (2977.0992 6656.4885) (2892.4885 6656.4885)
    ))
    ; P0391 -- see feature_dimensions_mm.csv
    ("02_CORNICES" 0 (
      (2967.4504 9938.9313) (3051.8321 9938.9313)
    ))
    ; P0392 -- see feature_dimensions_mm.csv
    ("02_CORNICES" 0 (
      (2967.4504 9938.9313) (2967.4504 9923.6641)
    ))
    ; P0393 -- see feature_dimensions_mm.csv
    ("02_CORNICES" 0 (
      (3051.8321 9923.6641) (2967.4504 9923.6641)
    ))
    ; P0394 -- see feature_dimensions_mm.csv
    ("02_CORNICES" 0 (
      (2967.4504 9923.6641) (2967.4504 9603.0534)
    ))
    ; P0395 -- see feature_dimensions_mm.csv
    ("02_CORNICES" 0 (
      (3051.8321 9603.0534) (2967.4504 9603.0534)
    ))
    ; P0396 -- see feature_dimensions_mm.csv
    ("02_CORNICES" 0 (
      (2977.0992 6977.0992) (3061.7099 6977.0992)
    ))
    ; P0397 -- see feature_dimensions_mm.csv
    ("02_CORNICES" 0 (
      (2977.0992 6977.0992) (2977.0992 6656.4885)
    ))
    ; P0398 -- see feature_dimensions_mm.csv
    ("02_CORNICES" 0 (
      (3061.7099 6656.4885) (2977.0992 6656.4885)
    ))
    ; P0399 -- see feature_dimensions_mm.csv
    ("02_CORNICES" 0 (
      (3051.8321 9938.9313) (3136.1985 9938.9313)
    ))
    ; P0400 -- see feature_dimensions_mm.csv
    ("02_CORNICES" 0 (
      (3051.8321 9938.9313) (3051.8321 9923.6641)
    ))
    ; P0401 -- see feature_dimensions_mm.csv
    ("02_CORNICES" 0 (
      (3136.1985 9923.6641) (3051.8321 9923.6641)
    ))
    ; P0402 -- see feature_dimensions_mm.csv
    ("02_CORNICES" 0 (
      (3051.8321 9923.6641) (3051.8321 9603.0534)
    ))
    ; P0403 -- see feature_dimensions_mm.csv
    ("02_CORNICES" 0 (
      (3136.1985 9603.0534) (3051.8321 9603.0534)
    ))
    ; P0404 -- see feature_dimensions_mm.csv
    ("02_CORNICES" 0 (
      (3061.7099 6977.0992) (3146.3053 6977.0992)
    ))
    ; P0405 -- see feature_dimensions_mm.csv
    ("02_CORNICES" 0 (
      (3061.7099 6977.0992) (3061.7099 6656.4885)
    ))
    ; P0406 -- see feature_dimensions_mm.csv
    ("02_CORNICES" 0 (
      (3146.3053 6656.4885) (3061.7099 6656.4885)
    ))
    ; P0407 -- see feature_dimensions_mm.csv
    ("02_CORNICES" 0 (
      (3074.8092 5679.3893) (3096.7481 5782.9924) (3129.771 5938.9313) (3083.0382 5938.9313)
    ))
    ; P0408 -- see feature_dimensions_mm.csv
    ("02_CORNICES" 0 (
      (3090.916 8076.3359) (3115.7557 7996.9466) (3140.5802 7996.9466) (3161.2824 7877.8626) (3215.084 7877.8626)
      (3235.771 7996.9466) (3256.4733 7996.9466) (3277.1603 8076.3359) (3504.7939 8076.3359) (3529.6336 7996.9466)
      (3554.458 7996.9466) (3575.1603 7877.8626) (3628.9618 7877.8626) (3649.6489 7996.9466) (3670.3511 7996.9466)
      (3691.0382 8076.3359) (3862.5954 8076.3359) (3918.6718 8076.3359) (3943.5115 7996.9466) (3968.3359 7996.9466)
      (3989.0382 7877.8626) (4042.8397 7877.8626) (4063.5267 7996.9466) (4084.229 7996.9466) (4104.916 8076.3359)
      (4213.7405 8076.3359) (4332.5496 8076.3359) (4357.3893 7996.9466) (4382.2137 7996.9466) (4402.916 7877.8626)
      (4456.7176 7877.8626) (4477.4046 7996.9466) (4498.1069 7996.9466) (4518.7939 8076.3359) (4534.3511 8076.3359)
      (4746.4275 8076.3359) (4771.2672 7996.9466) (4796.0916 7996.9466) (4816.7939 7877.8626) (4870.5954 7877.8626)
      (4891.2824 7996.9466) (4911.9847 7996.9466) (4932.6718 8076.3359)
    ))
    ; P0409 -- see feature_dimensions_mm.csv
    ("02_CORNICES" 0 (
      (3136.1985 9938.9313) (3220.5649 9938.9313)
    ))
    ; P0410 -- see feature_dimensions_mm.csv
    ("02_CORNICES" 0 (
      (3136.1985 9938.9313) (3136.1985 9923.6641)
    ))
    ; P0411 -- see feature_dimensions_mm.csv
    ("02_CORNICES" 0 (
      (3220.5649 9923.6641) (3136.1985 9923.6641)
    ))
    ; P0412 -- see feature_dimensions_mm.csv
    ("02_CORNICES" 0 (
      (3136.1985 9923.6641) (3136.1985 9603.0534)
    ))
    ; P0413 -- see feature_dimensions_mm.csv
    ("02_CORNICES" 0 (
      (3220.5649 9603.0534) (3136.1985 9603.0534)
    ))
    ; P0414 -- see feature_dimensions_mm.csv
    ("02_CORNICES" 0 (
      (3146.3053 6977.0992) (3230.916 6977.0992)
    ))
    ; P0415 -- see feature_dimensions_mm.csv
    ("02_CORNICES" 0 (
      (3146.3053 6977.0992) (3146.3053 6656.4885)
    ))
    ; P0416 -- see feature_dimensions_mm.csv
    ("02_CORNICES" 0 (
      (3230.916 6656.4885) (3146.3053 6656.4885)
    ))
    ; P0417 -- see feature_dimensions_mm.csv
    ("02_CORNICES" 0 (
      (3220.5649 9938.9313) (3304.9466 9938.9313)
    ))
    ; P0418 -- see feature_dimensions_mm.csv
    ("02_CORNICES" 0 (
      (3220.5649 9938.9313) (3220.5649 9923.6641)
    ))
    ; P0419 -- see feature_dimensions_mm.csv
    ("02_CORNICES" 0 (
      (3304.9466 9923.6641) (3220.5649 9923.6641)
    ))
    ; P0420 -- see feature_dimensions_mm.csv
    ("02_CORNICES" 0 (
      (3220.5649 9923.6641) (3220.5649 9603.0534)
    ))
    ; P0421 -- see feature_dimensions_mm.csv
    ("02_CORNICES" 0 (
      (3304.9466 9603.0534) (3220.5649 9603.0534)
    ))
    ; P0422 -- see feature_dimensions_mm.csv
    ("02_CORNICES" 0 (
      (3230.916 6977.0992) (3315.5267 6977.0992)
    ))
    ; P0423 -- see feature_dimensions_mm.csv
    ("02_CORNICES" 0 (
      (3230.916 6977.0992) (3230.916 6656.4885)
    ))
    ; P0424 -- see feature_dimensions_mm.csv
    ("02_CORNICES" 0 (
      (3315.5267 6656.4885) (3230.916 6656.4885)
    ))
    ; P0425 -- see feature_dimensions_mm.csv
    ("02_CORNICES" 0 (
      (3304.9466 9938.9313) (3389.313 9938.9313)
    ))
    ; P0426 -- see feature_dimensions_mm.csv
    ("02_CORNICES" 0 (
      (3304.9466 9938.9313) (3304.9466 9923.6641)
    ))
    ; P0427 -- see feature_dimensions_mm.csv
    ("02_CORNICES" 0 (
      (3389.313 9923.6641) (3304.9466 9923.6641)
    ))
    ; P0428 -- see feature_dimensions_mm.csv
    ("02_CORNICES" 0 (
      (3304.9466 9923.6641) (3304.9466 9603.0534)
    ))
    ; P0429 -- see feature_dimensions_mm.csv
    ("02_CORNICES" 0 (
      (3389.313 9603.0534) (3304.9466 9603.0534)
    ))
    ; P0430 -- see feature_dimensions_mm.csv
    ("02_CORNICES" 0 (
      (3315.5267 6977.0992) (3400.1221 6977.0992)
    ))
    ; P0431 -- see feature_dimensions_mm.csv
    ("02_CORNICES" 0 (
      (3315.5267 6977.0992) (3315.5267 6656.4885)
    ))
    ; P0432 -- see feature_dimensions_mm.csv
    ("02_CORNICES" 0 (
      (3400.1221 6656.4885) (3315.5267 6656.4885)
    ))
    ; P0433 -- see feature_dimensions_mm.csv
    ("02_CORNICES" 0 (
      (3389.313 9938.9313) (3473.6794 9938.9313)
    ))
    ; P0434 -- see feature_dimensions_mm.csv
    ("02_CORNICES" 0 (
      (3389.313 9938.9313) (3389.313 9923.6641)
    ))
    ; P0435 -- see feature_dimensions_mm.csv
    ("02_CORNICES" 0 (
      (3473.6794 9923.6641) (3389.313 9923.6641)
    ))
    ; P0436 -- see feature_dimensions_mm.csv
    ("02_CORNICES" 0 (
      (3389.313 9923.6641) (3389.313 9603.0534)
    ))
    ; P0437 -- see feature_dimensions_mm.csv
    ("02_CORNICES" 0 (
      (3473.6794 9603.0534) (3389.313 9603.0534)
    ))
    ; P0438 -- see feature_dimensions_mm.csv
    ("02_CORNICES" 0 (
      (3400.1221 6977.0992) (3484.7328 6977.0992)
    ))
    ; P0439 -- see feature_dimensions_mm.csv
    ("02_CORNICES" 0 (
      (3400.1221 6977.0992) (3400.1221 6656.4885)
    ))
    ; P0440 -- see feature_dimensions_mm.csv
    ("02_CORNICES" 0 (
      (3484.7328 6656.4885) (3400.1221 6656.4885)
    ))
    ; P0441 -- see feature_dimensions_mm.csv
    ("02_CORNICES" 0 (
      (3473.6794 9938.9313) (3558.0611 9938.9313)
    ))
    ; P0442 -- see feature_dimensions_mm.csv
    ("02_CORNICES" 0 (
      (3473.6794 9938.9313) (3473.6794 9923.6641)
    ))
    ; P0443 -- see feature_dimensions_mm.csv
    ("02_CORNICES" 0 (
      (3558.0611 9923.6641) (3473.6794 9923.6641)
    ))
    ; P0444 -- see feature_dimensions_mm.csv
    ("02_CORNICES" 0 (
      (3473.6794 9923.6641) (3473.6794 9603.0534)
    ))
    ; P0445 -- see feature_dimensions_mm.csv
    ("02_CORNICES" 0 (
      (3558.0611 9603.0534) (3473.6794 9603.0534)
    ))
    ; P0446 -- see feature_dimensions_mm.csv
    ("02_CORNICES" 0 (
      (3484.7328 6977.0992) (3569.3435 6977.0992)
    ))
    ; P0447 -- see feature_dimensions_mm.csv
    ("02_CORNICES" 0 (
      (3484.7328 6977.0992) (3484.7328 6656.4885)
    ))
    ; P0448 -- see feature_dimensions_mm.csv
    ("02_CORNICES" 0 (
      (3569.3435 6656.4885) (3484.7328 6656.4885)
    ))
    ; P0449 -- see feature_dimensions_mm.csv
    ("02_CORNICES" 0 (
      (3541.9847 2625.9542) (3832.0611 2625.9542)
    ))
    ; P0450 -- see feature_dimensions_mm.csv
    ("02_CORNICES" 0 (
      (3558.0611 9938.9313) (3642.4275 9938.9313)
    ))
    ; P0451 -- see feature_dimensions_mm.csv
    ("02_CORNICES" 0 (
      (3558.0611 9938.9313) (3558.0611 9923.6641)
    ))
    ; P0452 -- see feature_dimensions_mm.csv
    ("02_CORNICES" 0 (
      (3642.4275 9923.6641) (3558.0611 9923.6641)
    ))
    ; P0453 -- see feature_dimensions_mm.csv
    ("02_CORNICES" 0 (
      (3558.0611 9923.6641) (3558.0611 9603.0534)
    ))
    ; P0454 -- see feature_dimensions_mm.csv
    ("02_CORNICES" 0 (
      (3642.4275 9603.0534) (3558.0611 9603.0534)
    ))
    ; P0455 -- see feature_dimensions_mm.csv
    ("02_CORNICES" 0 (
      (3569.3435 6977.0992) (3653.9389 6977.0992)
    ))
    ; P0456 -- see feature_dimensions_mm.csv
    ("02_CORNICES" 0 (
      (3569.3435 6977.0992) (3569.3435 6656.4885)
    ))
    ; P0457 -- see feature_dimensions_mm.csv
    ("02_CORNICES" 0 (
      (3653.9389 6656.4885) (3569.3435 6656.4885)
    ))
    ; P0458 -- see feature_dimensions_mm.csv
    ("02_CORNICES" 0 (
      (3593.5573 2384.7023) (3574.3053 2474.7328)
    ))
    ; P0459 -- see feature_dimensions_mm.csv
    ("02_CORNICES" 0 (
      (3779.8473 2381.6794) (3594.1985 2381.6794)
    ))
    ; P0460 -- see feature_dimensions_mm.csv
    ("02_CORNICES" 0 (
      (3642.4275 9938.9313) (3726.7939 9938.9313)
    ))
    ; P0461 -- see feature_dimensions_mm.csv
    ("02_CORNICES" 0 (
      (3642.4275 9938.9313) (3642.4275 9923.6641)
    ))
    ; P0462 -- see feature_dimensions_mm.csv
    ("02_CORNICES" 0 (
      (3726.7939 9923.6641) (3642.4275 9923.6641)
    ))
    ; P0463 -- see feature_dimensions_mm.csv
    ("02_CORNICES" 0 (
      (3642.4275 9923.6641) (3642.4275 9603.0534)
    ))
    ; P0464 -- see feature_dimensions_mm.csv
    ("02_CORNICES" 0 (
      (3726.7939 9603.0534) (3642.4275 9603.0534)
    ))
    ; P0465 -- see feature_dimensions_mm.csv
    ("02_CORNICES" 0 (
      (3653.9389 6977.0992) (3738.5496 6977.0992)
    ))
    ; P0466 -- see feature_dimensions_mm.csv
    ("02_CORNICES" 0 (
      (3653.9389 6977.0992) (3653.9389 6656.4885)
    ))
    ; P0467 -- see feature_dimensions_mm.csv
    ("02_CORNICES" 0 (
      (3738.5496 6656.4885) (3653.9389 6656.4885)
    ))
    ; P0468 -- see feature_dimensions_mm.csv
    ("02_CORNICES" 0 (
      (3726.7939 9938.9313) (3811.1756 9938.9313)
    ))
    ; P0469 -- see feature_dimensions_mm.csv
    ("02_CORNICES" 0 (
      (3726.7939 9938.9313) (3726.7939 9923.6641)
    ))
    ; P0470 -- see feature_dimensions_mm.csv
    ("02_CORNICES" 0 (
      (3811.1756 9923.6641) (3726.7939 9923.6641)
    ))
    ; P0471 -- see feature_dimensions_mm.csv
    ("02_CORNICES" 0 (
      (3726.7939 9923.6641) (3726.7939 9603.0534)
    ))
    ; P0472 -- see feature_dimensions_mm.csv
    ("02_CORNICES" 0 (
      (3811.1756 9603.0534) (3726.7939 9603.0534)
    ))
    ; P0473 -- see feature_dimensions_mm.csv
    ("02_CORNICES" 0 (
      (3738.5496 6977.0992) (3823.1603 6977.0992)
    ))
    ; P0474 -- see feature_dimensions_mm.csv
    ("02_CORNICES" 0 (
      (3738.5496 6977.0992) (3738.5496 6656.4885)
    ))
    ; P0475 -- see feature_dimensions_mm.csv
    ("02_CORNICES" 0 (
      (3823.1603 6656.4885) (3738.5496 6656.4885)
    ))
    ; P0476 -- see feature_dimensions_mm.csv
    ("02_CORNICES" 0 (
      (3799.7405 2474.7328) (3780.4885 2384.7023)
    ))
    ; P0477 -- see feature_dimensions_mm.csv
    ("02_CORNICES" 0 (
      (3811.1756 9938.9313) (3895.542 9938.9313)
    ))
    ; P0478 -- see feature_dimensions_mm.csv
    ("02_CORNICES" 0 (
      (3811.1756 9938.9313) (3811.1756 9923.6641)
    ))
    ; P0479 -- see feature_dimensions_mm.csv
    ("02_CORNICES" 0 (
      (3895.542 9923.6641) (3811.1756 9923.6641)
    ))
    ; P0480 -- see feature_dimensions_mm.csv
    ("02_CORNICES" 0 (
      (3811.1756 9923.6641) (3811.1756 9603.0534)
    ))
    ; P0481 -- see feature_dimensions_mm.csv
    ("02_CORNICES" 0 (
      (3895.542 9603.0534) (3811.1756 9603.0534)
    ))
    ; P0482 -- see feature_dimensions_mm.csv
    ("02_CORNICES" 0 (
      (3823.1603 6977.0992) (3907.7557 6977.0992)
    ))
    ; P0483 -- see feature_dimensions_mm.csv
    ("02_CORNICES" 0 (
      (3823.1603 6977.0992) (3823.1603 6656.4885)
    ))
    ; P0484 -- see feature_dimensions_mm.csv
    ("02_CORNICES" 0 (
      (3907.7557 6656.4885) (3823.1603 6656.4885)
    ))
    ; P0485 -- see feature_dimensions_mm.csv
    ("02_CORNICES" 0 (
      (3895.542 9938.9313) (3979.9084 9938.9313)
    ))
    ; P0486 -- see feature_dimensions_mm.csv
    ("02_CORNICES" 0 (
      (3895.542 9938.9313) (3895.542 9923.6641)
    ))
    ; P0487 -- see feature_dimensions_mm.csv
    ("02_CORNICES" 0 (
      (3979.9084 9923.6641) (3895.542 9923.6641)
    ))
    ; P0488 -- see feature_dimensions_mm.csv
    ("02_CORNICES" 0 (
      (3895.542 9923.6641) (3895.542 9603.0534)
    ))
    ; P0489 -- see feature_dimensions_mm.csv
    ("02_CORNICES" 0 (
      (3979.9084 9603.0534) (3895.542 9603.0534)
    ))
    ; P0490 -- see feature_dimensions_mm.csv
    ("02_CORNICES" 0 (
      (3907.7557 6977.0992) (3992.3664 6977.0992)
    ))
    ; P0491 -- see feature_dimensions_mm.csv
    ("02_CORNICES" 0 (
      (3907.7557 6977.0992) (3907.7557 6656.4885)
    ))
    ; P0492 -- see feature_dimensions_mm.csv
    ("02_CORNICES" 0 (
      (3992.3664 6656.4885) (3907.7557 6656.4885)
    ))
    ; P0493 -- see feature_dimensions_mm.csv
    ("02_CORNICES" 0 (
      (3979.9084 9938.9313) (4064.2901 9938.9313)
    ))
    ; P0494 -- see feature_dimensions_mm.csv
    ("02_CORNICES" 0 (
      (3979.9084 9938.9313) (3979.9084 9923.6641)
    ))
    ; P0495 -- see feature_dimensions_mm.csv
    ("02_CORNICES" 0 (
      (4064.2901 9923.6641) (3979.9084 9923.6641)
    ))
    ; P0496 -- see feature_dimensions_mm.csv
    ("02_CORNICES" 0 (
      (3979.9084 9923.6641) (3979.9084 9603.0534)
    ))
    ; P0497 -- see feature_dimensions_mm.csv
    ("02_CORNICES" 0 (
      (4064.2901 9603.0534) (3979.9084 9603.0534)
    ))
    ; P0498 -- see feature_dimensions_mm.csv
    ("02_CORNICES" 0 (
      (3984.7328 3633.5878) (4564.8855 3633.5878)
    ))
    ; P0499 -- see feature_dimensions_mm.csv
    ("02_CORNICES" 0 (
      (3992.3664 6977.0992) (4076.9771 6977.0992)
    ))
    ; P0500 -- see feature_dimensions_mm.csv
    ("02_CORNICES" 0 (
      (3992.3664 6977.0992) (3992.3664 6656.4885)
    ))
    ; P0501 -- see feature_dimensions_mm.csv
    ("02_CORNICES" 0 (
      (4076.9771 6656.4885) (3992.3664 6656.4885)
    ))
    ; P0502 -- see feature_dimensions_mm.csv
    ("02_CORNICES" 0 (
      (4064.2901 9938.9313) (4148.6565 9938.9313)
    ))
    ; P0503 -- see feature_dimensions_mm.csv
    ("02_CORNICES" 0 (
      (4064.2901 9938.9313) (4064.2901 9923.6641)
    ))
    ; P0504 -- see feature_dimensions_mm.csv
    ("02_CORNICES" 0 (
      (4148.6565 9923.6641) (4064.2901 9923.6641)
    ))
    ; P0505 -- see feature_dimensions_mm.csv
    ("02_CORNICES" 0 (
      (4064.2901 9923.6641) (4064.2901 9603.0534)
    ))
    ; P0506 -- see feature_dimensions_mm.csv
    ("02_CORNICES" 0 (
      (4148.6565 9603.0534) (4064.2901 9603.0534)
    ))
    ; P0507 -- see feature_dimensions_mm.csv
    ("02_CORNICES" 0 (
      (4076.9771 6977.0992) (4161.5725 6977.0992)
    ))
    ; P0508 -- see feature_dimensions_mm.csv
    ("02_CORNICES" 0 (
      (4076.9771 6977.0992) (4076.9771 6656.4885)
    ))
    ; P0509 -- see feature_dimensions_mm.csv
    ("02_CORNICES" 0 (
      (4161.5725 6656.4885) (4076.9771 6656.4885)
    ))
    ; P0510 -- see feature_dimensions_mm.csv
    ("02_CORNICES" 0 (
      (4148.6565 9938.9313) (4233.0229 9938.9313)
    ))
    ; P0511 -- see feature_dimensions_mm.csv
    ("02_CORNICES" 0 (
      (4148.6565 9938.9313) (4148.6565 9923.6641)
    ))
    ; P0512 -- see feature_dimensions_mm.csv
    ("02_CORNICES" 0 (
      (4233.0229 9923.6641) (4148.6565 9923.6641)
    ))
    ; P0513 -- see feature_dimensions_mm.csv
    ("02_CORNICES" 0 (
      (4148.6565 9923.6641) (4148.6565 9603.0534)
    ))
    ; P0514 -- see feature_dimensions_mm.csv
    ("02_CORNICES" 0 (
      (4233.0229 9603.0534) (4148.6565 9603.0534)
    ))
    ; P0515 -- see feature_dimensions_mm.csv
    ("02_CORNICES" 0 (
      (4161.5725 6977.0992) (4246.1832 6977.0992)
    ))
    ; P0516 -- see feature_dimensions_mm.csv
    ("02_CORNICES" 0 (
      (4161.5725 6977.0992) (4161.5725 6656.4885)
    ))
    ; P0517 -- see feature_dimensions_mm.csv
    ("02_CORNICES" 0 (
      (4246.1832 6656.4885) (4161.5725 6656.4885)
    ))
    ; P0518 -- see feature_dimensions_mm.csv
    ("02_CORNICES" 0 (
      (4233.0229 9938.9313) (4317.3893 9938.9313)
    ))
    ; P0519 -- see feature_dimensions_mm.csv
    ("02_CORNICES" 0 (
      (4233.0229 9938.9313) (4233.0229 9923.6641)
    ))
    ; P0520 -- see feature_dimensions_mm.csv
    ("02_CORNICES" 0 (
      (4317.3893 9923.6641) (4233.0229 9923.6641)
    ))
    ; P0521 -- see feature_dimensions_mm.csv
    ("02_CORNICES" 0 (
      (4233.0229 9923.6641) (4233.0229 9603.0534)
    ))
    ; P0522 -- see feature_dimensions_mm.csv
    ("02_CORNICES" 0 (
      (4317.3893 9603.0534) (4233.0229 9603.0534)
    ))
    ; P0523 -- see feature_dimensions_mm.csv
    ("02_CORNICES" 0 (
      (4246.1832 6977.0992) (4330.7939 6977.0992)
    ))
    ; P0524 -- see feature_dimensions_mm.csv
    ("02_CORNICES" 0 (
      (4246.1832 6977.0992) (4246.1832 6656.4885)
    ))
    ; P0525 -- see feature_dimensions_mm.csv
    ("02_CORNICES" 0 (
      (4330.7939 6656.4885) (4246.1832 6656.4885)
    ))
    ; P0526 -- see feature_dimensions_mm.csv
    ("02_CORNICES" 0 (
      (4317.3893 9938.9313) (4401.771 9938.9313)
    ))
    ; P0527 -- see feature_dimensions_mm.csv
    ("02_CORNICES" 0 (
      (4317.3893 9938.9313) (4317.3893 9923.6641)
    ))
    ; P0528 -- see feature_dimensions_mm.csv
    ("02_CORNICES" 0 (
      (4401.771 9923.6641) (4317.3893 9923.6641)
    ))
    ; P0529 -- see feature_dimensions_mm.csv
    ("02_CORNICES" 0 (
      (4317.3893 9923.6641) (4317.3893 9603.0534)
    ))
    ; P0530 -- see feature_dimensions_mm.csv
    ("02_CORNICES" 0 (
      (4401.771 9603.0534) (4317.3893 9603.0534)
    ))
    ; P0531 -- see feature_dimensions_mm.csv
    ("02_CORNICES" 0 (
      (4330.7939 6977.0992) (4415.3893 6977.0992)
    ))
    ; P0532 -- see feature_dimensions_mm.csv
    ("02_CORNICES" 0 (
      (4330.7939 6977.0992) (4330.7939 6656.4885)
    ))
    ; P0533 -- see feature_dimensions_mm.csv
    ("02_CORNICES" 0 (
      (4415.3893 6656.4885) (4330.7939 6656.4885)
    ))
    ; P0534 -- see feature_dimensions_mm.csv
    ("02_CORNICES" 0 (
      (4519.084 1862.5954) (4351.145 1862.5954)
    ))
    ; P0535 -- see feature_dimensions_mm.csv
    ("02_CORNICES" 0 (
      (4401.771 9938.9313) (4486.1374 9938.9313)
    ))
    ; P0536 -- see feature_dimensions_mm.csv
    ("02_CORNICES" 0 (
      (4401.771 9938.9313) (4401.771 9923.6641)
    ))
    ; P0537 -- see feature_dimensions_mm.csv
    ("02_CORNICES" 0 (
      (4486.1374 9923.6641) (4401.771 9923.6641)
    ))
    ; P0538 -- see feature_dimensions_mm.csv
    ("02_CORNICES" 0 (
      (4401.771 9923.6641) (4401.771 9603.0534)
    ))
    ; P0539 -- see feature_dimensions_mm.csv
    ("02_CORNICES" 0 (
      (4486.1374 9603.0534) (4401.771 9603.0534)
    ))
    ; P0540 -- see feature_dimensions_mm.csv
    ("02_CORNICES" 0 (
      (4415.3893 6977.0992) (4500.0 6977.0992)
    ))
    ; P0541 -- see feature_dimensions_mm.csv
    ("02_CORNICES" 0 (
      (4415.3893 6977.0992) (4415.3893 6656.4885)
    ))
    ; P0542 -- see feature_dimensions_mm.csv
    ("02_CORNICES" 0 (
      (4500.0 6656.4885) (4415.3893 6656.4885)
    ))
    ; P0543 -- see feature_dimensions_mm.csv
    ("02_CORNICES" 0 (
      (4486.1374 9938.9313) (4570.5038 9938.9313)
    ))
    ; P0544 -- see feature_dimensions_mm.csv
    ("02_CORNICES" 0 (
      (4486.1374 9938.9313) (4486.1374 9923.6641)
    ))
    ; P0545 -- see feature_dimensions_mm.csv
    ("02_CORNICES" 0 (
      (4570.5038 9923.6641) (4486.1374 9923.6641)
    ))
    ; P0546 -- see feature_dimensions_mm.csv
    ("02_CORNICES" 0 (
      (4486.1374 9923.6641) (4486.1374 9603.0534)
    ))
    ; P0547 -- see feature_dimensions_mm.csv
    ("02_CORNICES" 0 (
      (4570.5038 9603.0534) (4486.1374 9603.0534)
    ))
    ; P0548 -- see feature_dimensions_mm.csv
    ("02_CORNICES" 0 (
      (4500.0 6977.0992) (4584.6107 6977.0992)
    ))
    ; P0549 -- see feature_dimensions_mm.csv
    ("02_CORNICES" 0 (
      (4500.0 6977.0992) (4500.0 6656.4885)
    ))
    ; P0550 -- see feature_dimensions_mm.csv
    ("02_CORNICES" 0 (
      (4584.6107 6656.4885) (4500.0 6656.4885)
    ))
    ; P0551 -- see feature_dimensions_mm.csv
    ("02_CORNICES" 0 (
      (4564.8855 3679.3893) (4595.4198 3679.3893) (4992.3664 3679.3893) (5022.9008 3679.3893)
    ))
    ; P0552 -- see feature_dimensions_mm.csv
    ("02_CORNICES" 0 (
      (4564.8855 3679.3893) (4564.8855 3633.5878)
    ))
    ; P0553 -- see feature_dimensions_mm.csv
    ("02_CORNICES" 0 (
      (4595.4198 3740.458) (4564.8855 3740.458) (4564.8855 3679.3893)
    ))
    ; P0554 -- see feature_dimensions_mm.csv
    ("02_CORNICES" 0 (
      (4564.8855 3633.5878) (4595.4198 3633.5878) (4992.3664 3633.5878) (5022.9008 3633.5878)
    ))
    ; P0555 -- see feature_dimensions_mm.csv
    ("02_CORNICES" 0 (
      (4570.5038 9938.9313) (4654.8855 9938.9313)
    ))
    ; P0556 -- see feature_dimensions_mm.csv
    ("02_CORNICES" 0 (
      (4570.5038 9938.9313) (4570.5038 9923.6641)
    ))
    ; P0557 -- see feature_dimensions_mm.csv
    ("02_CORNICES" 0 (
      (4654.8855 9923.6641) (4570.5038 9923.6641)
    ))
    ; P0558 -- see feature_dimensions_mm.csv
    ("02_CORNICES" 0 (
      (4570.5038 9923.6641) (4570.5038 9603.0534)
    ))
    ; P0559 -- see feature_dimensions_mm.csv
    ("02_CORNICES" 0 (
      (4654.8855 9603.0534) (4570.5038 9603.0534)
    ))
    ; P0560 -- see feature_dimensions_mm.csv
    ("02_CORNICES" 0 (
      (4584.6107 6977.0992) (4669.2061 6977.0992)
    ))
    ; P0561 -- see feature_dimensions_mm.csv
    ("02_CORNICES" 0 (
      (4584.6107 6977.0992) (4584.6107 6656.4885)
    ))
    ; P0562 -- see feature_dimensions_mm.csv
    ("02_CORNICES" 0 (
      (4669.2061 6656.4885) (4584.6107 6656.4885)
    ))
    ; P0563 -- see feature_dimensions_mm.csv
    ("02_CORNICES" 0 (
      (4654.8855 9938.9313) (4739.2519 9938.9313)
    ))
    ; P0564 -- see feature_dimensions_mm.csv
    ("02_CORNICES" 0 (
      (4654.8855 9938.9313) (4654.8855 9923.6641)
    ))
    ; P0565 -- see feature_dimensions_mm.csv
    ("02_CORNICES" 0 (
      (4739.2519 9923.6641) (4654.8855 9923.6641)
    ))
    ; P0566 -- see feature_dimensions_mm.csv
    ("02_CORNICES" 0 (
      (4654.8855 9923.6641) (4654.8855 9603.0534)
    ))
    ; P0567 -- see feature_dimensions_mm.csv
    ("02_CORNICES" 0 (
      (4739.2519 9603.0534) (4654.8855 9603.0534)
    ))
    ; P0568 -- see feature_dimensions_mm.csv
    ("02_CORNICES" 0 (
      (4669.2061 6977.0992) (4753.8168 6977.0992)
    ))
    ; P0569 -- see feature_dimensions_mm.csv
    ("02_CORNICES" 0 (
      (4669.2061 6977.0992) (4669.2061 6656.4885)
    ))
    ; P0570 -- see feature_dimensions_mm.csv
    ("02_CORNICES" 0 (
      (4753.8168 6656.4885) (4669.2061 6656.4885)
    ))
    ; P0571 -- see feature_dimensions_mm.csv
    ("02_CORNICES" 0 (
      (4739.2519 9938.9313) (4823.6183 9938.9313)
    ))
    ; P0572 -- see feature_dimensions_mm.csv
    ("02_CORNICES" 0 (
      (4739.2519 9938.9313) (4739.2519 9923.6641)
    ))
    ; P0573 -- see feature_dimensions_mm.csv
    ("02_CORNICES" 0 (
      (4823.6183 9923.6641) (4739.2519 9923.6641)
    ))
    ; P0574 -- see feature_dimensions_mm.csv
    ("02_CORNICES" 0 (
      (4739.2519 9923.6641) (4739.2519 9603.0534)
    ))
    ; P0575 -- see feature_dimensions_mm.csv
    ("02_CORNICES" 0 (
      (4823.6183 9603.0534) (4739.2519 9603.0534)
    ))
    ; P0576 -- see feature_dimensions_mm.csv
    ("02_CORNICES" 0 (
      (4753.8168 6977.0992) (4838.4275 6977.0992)
    ))
    ; P0577 -- see feature_dimensions_mm.csv
    ("02_CORNICES" 0 (
      (4753.8168 6977.0992) (4753.8168 6656.4885)
    ))
    ; P0578 -- see feature_dimensions_mm.csv
    ("02_CORNICES" 0 (
      (4838.4275 6656.4885) (4753.8168 6656.4885)
    ))
    ; P0579 -- see feature_dimensions_mm.csv
    ("02_CORNICES" 0 (
      (8687.0229 8320.6107) (4793.8931 8320.6107)
    ))
    ; P0580 -- see feature_dimensions_mm.csv
    ("02_CORNICES" 0 (
      (4977.0992 8137.4046) (4793.8931 8137.4046) (4793.8931 8320.6107)
    ))
    ; P0581 -- see feature_dimensions_mm.csv
    ("02_CORNICES" 0 (
      (4793.8931 8320.6107) (4641.2214 8320.6107) (4641.2214 8564.8855) (4641.2214 8641.2214) (4860.0916 8641.2214)
      (4883.9695 8561.8321) (4907.8473 8561.8321) (4927.7557 8442.7481) (4979.4809 8442.7481) (4999.3893 8561.8321)
      (5019.2824 8561.8321) (5039.1756 8641.2214) (5258.0611 8641.2214) (5281.9389 8561.8321) (5305.8168 8561.8321)
      (5325.7099 8442.7481) (5377.4504 8442.7481) (5397.3435 8561.8321) (5417.2366 8561.8321) (5437.145 8641.2214)
      (5656.0153 8641.2214) (5679.8931 8561.8321) (5703.771 8561.8321) (5723.6641 8442.7481) (5775.4046 8442.7481)
      (5795.2977 8561.8321) (5815.2061 8561.8321) (5835.0992 8641.2214) (6053.9847 8641.2214) (6077.8626 8561.8321)
      (6101.7405 8561.8321) (6121.6336 8442.7481) (6173.3588 8442.7481) (6193.2672 8561.8321) (6213.1603 8561.8321)
      (6233.0534 8641.2214) (6451.9389 8641.2214) (6475.8168 8561.8321) (6499.6947 8561.8321) (6519.5878 8442.7481)
      (6571.3282 8442.7481) (6591.2214 8561.8321) (6611.1145 8561.8321) (6631.0229 8641.2214) (6849.8931 8641.2214)
      (6873.771 8561.8321) (6897.6489 8561.8321) (6917.5573 8442.7481) (6969.2824 8442.7481) (6989.1756 8561.8321)
      (7009.084 8561.8321) (7028.9771 8641.2214) (7247.8626 8641.2214) (7271.7405 8561.8321) (7295.6183 8561.8321)
      (7315.5115 8442.7481) (7367.2519 8442.7481) (7387.145 8561.8321) (7407.0382 8561.8321) (7426.9313 8641.2214)
      (7645.8168 8641.2214) (7669.6947 8561.8321) (7693.5725 8561.8321) (7713.4656 8442.7481) (7765.2061 8442.7481)
      (7785.0992 8561.8321) (7804.9924 8561.8321) (7824.9008 8641.2214) (8043.771 8641.2214) (8067.6489 8561.8321)
      (8091.5267 8561.8321) (8111.4351 8442.7481) (8163.1603 8442.7481) (8183.0687 8561.8321) (8202.9618 8561.8321)
      (8222.855 8641.2214) (8441.7405 8641.2214) (8465.6183 8561.8321) (8489.4962 8561.8321) (8509.3893 8442.7481)
      (8561.1298 8442.7481) (8581.0229 8561.8321) (8600.916 8561.8321) (8620.8244 8641.2214) (8839.6947 8641.2214)
      (8839.6947 8320.6107) (8687.0229 8320.6107)
    ))
    ; P0582 -- see feature_dimensions_mm.csv
    ("02_CORNICES" 0 (
      (4823.6183 9938.9313) (4908.0 9938.9313)
    ))
    ; P0583 -- see feature_dimensions_mm.csv
    ("02_CORNICES" 0 (
      (4823.6183 9938.9313) (4823.6183 9923.6641)
    ))
    ; P0584 -- see feature_dimensions_mm.csv
    ("02_CORNICES" 0 (
      (4908.0 9923.6641) (4823.6183 9923.6641)
    ))
    ; P0585 -- see feature_dimensions_mm.csv
    ("02_CORNICES" 0 (
      (4823.6183 9923.6641) (4823.6183 9603.0534)
    ))
    ; P0586 -- see feature_dimensions_mm.csv
    ("02_CORNICES" 0 (
      (4908.0 9603.0534) (4823.6183 9603.0534)
    ))
    ; P0587 -- see feature_dimensions_mm.csv
    ("02_CORNICES" 0 (
      (4838.4275 6977.0992) (4923.0229 6977.0992)
    ))
    ; P0588 -- see feature_dimensions_mm.csv
    ("02_CORNICES" 0 (
      (4838.4275 6977.0992) (4838.4275 6656.4885)
    ))
    ; P0589 -- see feature_dimensions_mm.csv
    ("02_CORNICES" 0 (
      (4923.0229 6656.4885) (4838.4275 6656.4885)
    ))
    ; P0590 -- see feature_dimensions_mm.csv
    ("02_CORNICES" 0 (
      (4908.0 9938.9313) (4992.3664 9938.9313) (4992.3664 9923.6641)
    ))
    ; P0591 -- see feature_dimensions_mm.csv
    ("02_CORNICES" 0 (
      (4908.0 9938.9313) (4908.0 9923.6641)
    ))
    ; P0592 -- see feature_dimensions_mm.csv
    ("02_CORNICES" 0 (
      (4992.3664 9923.6641) (4908.0 9923.6641)
    ))
    ; P0593 -- see feature_dimensions_mm.csv
    ("02_CORNICES" 0 (
      (4908.0 9923.6641) (4908.0 9603.0534)
    ))
    ; P0594 -- see feature_dimensions_mm.csv
    ("02_CORNICES" 0 (
      (4992.3664 9603.0534) (4908.0 9603.0534)
    ))
    ; P0595 -- see feature_dimensions_mm.csv
    ("02_CORNICES" 0 (
      (4923.0229 6977.0992) (4992.3664 6977.0992) (5007.6336 6977.0992) (5007.6336 6961.8321) (5007.6336 6656.4885)
    ))
    ; P0596 -- see feature_dimensions_mm.csv
    ("02_CORNICES" 0 (
      (4923.0229 6977.0992) (4923.0229 6656.4885)
    ))
    ; P0597 -- see feature_dimensions_mm.csv
    ("02_CORNICES" 0 (
      (5007.6336 6656.4885) (4992.3664 6656.4885) (4923.0229 6656.4885)
    ))
    ; P0598 -- see feature_dimensions_mm.csv
    ("02_CORNICES" 0 (
      (8671.7557 8137.4046) (4977.0992 8137.4046)
    ))
    ; P0599 -- see feature_dimensions_mm.csv
    ("02_CORNICES" 0 (
      (4977.0992 8137.4046) (4977.0992 8122.1374) (4977.0992 8076.3359)
    ))
    ; P0600 -- see feature_dimensions_mm.csv
    ("02_CORNICES" 0 (
      (5007.6336 9969.4656) (5007.6336 9923.6641) (4992.3664 9923.6641)
    ))
    ; P0601 -- see feature_dimensions_mm.csv
    ("02_CORNICES" 0 (
      (4992.3664 9923.6641) (4992.3664 9603.0534)
    ))
    ; P0602 -- see feature_dimensions_mm.csv
    ("02_CORNICES" 0 (
      (4992.3664 9603.0534) (4992.3664 9587.7863) (4992.3664 9572.5191)
    ))
    ; P0603 -- see feature_dimensions_mm.csv
    ("02_CORNICES" 0 (
      (4992.3664 8076.3359) (5160.3053 8076.3359) (5160.3053 7755.7252)
    ))
    ; P0604 -- see feature_dimensions_mm.csv
    ("02_CORNICES" 0 (
      (4992.3664 7374.0458) (8671.7557 7374.0458)
    ))
    ; P0605 -- see feature_dimensions_mm.csv
    ("02_CORNICES" 0 (
      (4992.3664 7312.9771) (8671.7557 7312.9771) (8671.7557 7358.7786) (8671.7557 7374.0458)
    ))
    ; P0606 -- see feature_dimensions_mm.csv
    ("02_CORNICES" 0 (
      (5007.6336 6625.9542) (4992.3664 6625.9542)
    ))
    ; P0607 -- see feature_dimensions_mm.csv
    ("02_CORNICES" 0 (
      (5007.6336 6625.9542) (5007.6336 6564.8855) (4992.3664 6564.8855)
    ))
    ; P0608 -- see feature_dimensions_mm.csv
    ("02_CORNICES" 0 (
      (8854.9618 6625.9542) (8732.8244 6473.2824) (8671.7557 6473.2824) (4992.3664 6473.2824)
    ))
    ; P0609 -- see feature_dimensions_mm.csv
    ("02_CORNICES" 0 (
      (5022.9008 3679.3893) (5022.9008 3740.458) (4992.3664 3740.458)
    ))
    ; P0610 -- see feature_dimensions_mm.csv
    ("02_CORNICES" 0 (
      (5160.3053 10259.542) (5053.4351 10122.1374) (5007.6336 10122.1374)
    ))
    ; P0611 -- see feature_dimensions_mm.csv
    ("02_CORNICES" 0 (
      (5007.6336 10122.1374) (5007.6336 9984.7328)
    ))
    ; P0612 -- see feature_dimensions_mm.csv
    ("02_CORNICES" 0 (
      (5007.6336 9984.7328) (5007.6336 9969.4656)
    ))
    ; P0613 -- see feature_dimensions_mm.csv
    ("02_CORNICES" 0 (
      (5007.6336 6656.4885) (5007.6336 6625.9542)
    ))
    ; P0614 -- see feature_dimensions_mm.csv
    ("02_CORNICES" 0 (
      (5068.7023 6625.9542) (5007.6336 6625.9542)
    ))
    ; P0615 -- see feature_dimensions_mm.csv
    ("02_CORNICES" 0 (
      (5022.9008 3679.3893) (5114.5038 3679.3893) (5114.5038 3633.5878)
    ))
    ; P0616 -- see feature_dimensions_mm.csv
    ("02_CORNICES" 0 (
      (5022.9008 3633.5878) (5022.9008 3679.3893)
    ))
    ; P0617 -- see feature_dimensions_mm.csv
    ("02_CORNICES" 0 (
      (5022.9008 3633.5878) (5114.5038 3633.5878)
    ))
    ; P0618 -- see feature_dimensions_mm.csv
    ("02_CORNICES" 0 (
      (5068.7023 6625.9542) (5068.7023 6961.8321)
    ))
    ; P0619 -- see feature_dimensions_mm.csv
    ("02_CORNICES" 0 (
      (5099.2366 6625.9542) (5068.7023 6625.9542)
    ))
    ; P0620 -- see feature_dimensions_mm.csv
    ("02_CORNICES" 0 (
      (5099.2366 6961.8321) (5099.2366 6625.9542)
    ))
    ; P0621 -- see feature_dimensions_mm.csv
    ("02_CORNICES" 0 (
      (5160.3053 6625.9542) (5099.2366 6625.9542)
    ))
    ; P0622 -- see feature_dimensions_mm.csv
    ("02_CORNICES" 0 (
      (5114.5038 3633.5878) (5175.5725 3633.5878) (5160.3053 3419.8473) (5137.4046 3389.313)
    ))
    ; P0623 -- see feature_dimensions_mm.csv
    ("02_CORNICES" 0 (
      (5160.3053 7755.7252) (7022.9008 7755.7252)
    ))
    ; P0624 -- see feature_dimensions_mm.csv
    ("02_CORNICES" 0 (
      (5160.3053 7755.7252) (5160.3053 7740.458)
    ))
    ; P0625 -- see feature_dimensions_mm.csv
    ("02_CORNICES" 0 (
      (5160.3053 7740.458) (5160.3053 7679.3893) (8671.7557 7679.3893)
    ))
    ; P0626 -- see feature_dimensions_mm.csv
    ("02_CORNICES" 1 (
      (5160.3053 7740.458) (5038.1679 7557.2519) (916.0305 7557.2519) (793.8931 7740.458)
    ))
    ; P0627 -- see feature_dimensions_mm.csv
    ("02_CORNICES" 0 (
      (5160.3053 6625.9542) (5160.3053 6961.8321)
    ))
    ; P0628 -- see feature_dimensions_mm.csv
    ("02_CORNICES" 0 (
      (5190.8397 6625.9542) (5160.3053 6625.9542)
    ))
    ; P0629 -- see feature_dimensions_mm.csv
    ("02_CORNICES" 0 (
      (5190.8397 6961.8321) (5190.8397 6625.9542)
    ))
    ; P0630 -- see feature_dimensions_mm.csv
    ("02_CORNICES" 0 (
      (5251.9084 6625.9542) (5190.8397 6625.9542)
    ))
    ; P0631 -- see feature_dimensions_mm.csv
    ("02_CORNICES" 0 (
      (5251.9084 6625.9542) (5251.9084 6961.8321)
    ))
    ; P0632 -- see feature_dimensions_mm.csv
    ("02_CORNICES" 0 (
      (5268.2595 6625.9542) (5251.9084 6625.9542)
    ))
    ; P0633 -- see feature_dimensions_mm.csv
    ("02_CORNICES" 0 (
      (5268.2595 6961.8321) (5268.2595 6625.9542)
    ))
    ; P0634 -- see feature_dimensions_mm.csv
    ("02_CORNICES" 0 (
      (5282.4427 6625.9542) (5268.2595 6625.9542)
    ))
    ; P0635 -- see feature_dimensions_mm.csv
    ("02_CORNICES" 0 (
      (5282.4427 6961.8321) (5282.4427 6625.9542)
    ))
    ; P0636 -- see feature_dimensions_mm.csv
    ("02_CORNICES" 0 (
      (5343.5115 6625.9542) (5282.4427 6625.9542)
    ))
    ; P0637 -- see feature_dimensions_mm.csv
    ("02_CORNICES" 0 (
      (5343.5115 6625.9542) (5343.5115 6961.8321)
    ))
    ; P0638 -- see feature_dimensions_mm.csv
    ("02_CORNICES" 0 (
      (5374.0458 6625.9542) (5343.5115 6625.9542)
    ))
    ; P0639 -- see feature_dimensions_mm.csv
    ("02_CORNICES" 0 (
      (5374.0458 6961.8321) (5374.0458 6625.9542)
    ))
    ; P0640 -- see feature_dimensions_mm.csv
    ("02_CORNICES" 0 (
      (5435.1145 6625.9542) (5374.0458 6625.9542)
    ))
    ; P0641 -- see feature_dimensions_mm.csv
    ("02_CORNICES" 0 (
      (5435.1145 6625.9542) (5435.1145 6961.8321)
    ))
    ; P0642 -- see feature_dimensions_mm.csv
    ("02_CORNICES" 0 (
      (5465.6489 6625.9542) (5435.1145 6625.9542)
    ))
    ; P0643 -- see feature_dimensions_mm.csv
    ("02_CORNICES" 0 (
      (5465.6489 6961.8321) (5465.6489 6625.9542)
    ))
    ; P0644 -- see feature_dimensions_mm.csv
    ("02_CORNICES" 0 (
      (5544.1679 6625.9542) (5465.6489 6625.9542)
    ))
    ; P0645 -- see feature_dimensions_mm.csv
    ("02_CORNICES" 0 (
      (5544.1679 6961.8321) (5544.1679 6625.9542)
    ))
    ; P0646 -- see feature_dimensions_mm.csv
    ("02_CORNICES" 0 (
      (5820.0611 6625.9542) (5544.1679 6625.9542)
    ))
    ; P0647 -- see feature_dimensions_mm.csv
    ("02_CORNICES" 0 (
      (5820.0611 6961.8321) (5820.0611 6625.9542)
    ))
    ; P0648 -- see feature_dimensions_mm.csv
    ("02_CORNICES" 0 (
      (6095.9695 6625.9542) (5820.0611 6625.9542)
    ))
    ; P0649 -- see feature_dimensions_mm.csv
    ("02_CORNICES" 0 (
      (6095.9695 6961.8321) (6095.9695 6625.9542)
    ))
    ; P0650 -- see feature_dimensions_mm.csv
    ("02_CORNICES" 0 (
      (6371.8626 6625.9542) (6095.9695 6625.9542)
    ))
    ; P0651 -- see feature_dimensions_mm.csv
    ("02_CORNICES" 0 (
      (6371.8626 6961.8321) (6371.8626 6625.9542)
    ))
    ; P0652 -- see feature_dimensions_mm.csv
    ("02_CORNICES" 0 (
      (6647.771 6625.9542) (6371.8626 6625.9542)
    ))
    ; P0653 -- see feature_dimensions_mm.csv
    ("02_CORNICES" 0 (
      (6647.771 6961.8321) (6647.771 6625.9542)
    ))
    ; P0654 -- see feature_dimensions_mm.csv
    ("02_CORNICES" 0 (
      (6923.6641 6625.9542) (6647.771 6625.9542)
    ))
    ; P0655 -- see feature_dimensions_mm.csv
    ("02_CORNICES" 0 (
      (6923.6641 6961.8321) (6923.6641 6625.9542)
    ))
    ; P0656 -- see feature_dimensions_mm.csv
    ("02_CORNICES" 0 (
      (7199.5573 6625.9542) (6923.6641 6625.9542)
    ))
    ; P0657 -- see feature_dimensions_mm.csv
    ("02_CORNICES" 0 (
      (7022.9008 7755.7252) (7039.6947 7755.7252)
    ))
    ; P0658 -- see feature_dimensions_mm.csv
    ("02_CORNICES" 0 (
      (7022.9008 7755.7252) (7022.9008 8122.1374) (7039.6947 8122.1374) (7039.6947 7755.7252)
    ))
    ; P0659 -- see feature_dimensions_mm.csv
    ("02_CORNICES" 0 (
      (7039.6947 7755.7252) (8671.7557 7755.7252) (8671.7557 7923.6641) (8671.7557 8122.1374) (8671.7557 8137.4046)
    ))
    ; P0660 -- see feature_dimensions_mm.csv
    ("02_CORNICES" 0 (
      (7199.5573 6961.8321) (7199.5573 6625.9542)
    ))
    ; P0661 -- see feature_dimensions_mm.csv
    ("02_CORNICES" 0 (
      (7475.4656 6625.9542) (7199.5573 6625.9542)
    ))
    ; P0662 -- see feature_dimensions_mm.csv
    ("02_CORNICES" 0 (
      (7475.4656 6961.8321) (7475.4656 6625.9542)
    ))
    ; P0663 -- see feature_dimensions_mm.csv
    ("02_CORNICES" 0 (
      (7751.3588 6625.9542) (7475.4656 6625.9542)
    ))
    ; P0664 -- see feature_dimensions_mm.csv
    ("02_CORNICES" 0 (
      (7751.3588 6961.8321) (7751.3588 6625.9542)
    ))
    ; P0665 -- see feature_dimensions_mm.csv
    ("02_CORNICES" 0 (
      (8027.2672 6625.9542) (7751.3588 6625.9542)
    ))
    ; P0666 -- see feature_dimensions_mm.csv
    ("02_CORNICES" 0 (
      (8152.6718 6625.9542) (8027.2672 6625.9542)
    ))
    ; P0667 -- see feature_dimensions_mm.csv
    ("02_CORNICES" 0 (
      (8027.2672 6625.9542) (8027.2672 6961.8321) (8152.6718 6961.8321)
    ))
    ; P0668 -- see feature_dimensions_mm.csv
    ("02_CORNICES" 0 (
      (8152.6718 6961.8321) (8183.2061 6961.8321)
    ))
    ; P0669 -- see feature_dimensions_mm.csv
    ("02_CORNICES" 0 (
      (8152.6718 6625.9542) (8152.6718 6961.8321)
    ))
    ; P0670 -- see feature_dimensions_mm.csv
    ("02_CORNICES" 0 (
      (8183.2061 6625.9542) (8152.6718 6625.9542)
    ))
    ; P0671 -- see feature_dimensions_mm.csv
    ("02_CORNICES" 0 (
      (8183.2061 6961.8321) (8244.2748 6961.8321)
    ))
    ; P0672 -- see feature_dimensions_mm.csv
    ("02_CORNICES" 0 (
      (8183.2061 6961.8321) (8183.2061 6625.9542)
    ))
    ; P0673 -- see feature_dimensions_mm.csv
    ("02_CORNICES" 0 (
      (8244.2748 6625.9542) (8183.2061 6625.9542)
    ))
    ; P0674 -- see feature_dimensions_mm.csv
    ("02_CORNICES" 0 (
      (8244.2748 6961.8321) (8274.8092 6961.8321)
    ))
    ; P0675 -- see feature_dimensions_mm.csv
    ("02_CORNICES" 0 (
      (8244.2748 6625.9542) (8244.2748 6961.8321)
    ))
    ; P0676 -- see feature_dimensions_mm.csv
    ("02_CORNICES" 0 (
      (8274.8092 6625.9542) (8244.2748 6625.9542)
    ))
    ; P0677 -- see feature_dimensions_mm.csv
    ("02_CORNICES" 0 (
      (8274.8092 6961.8321) (8303.1603 6961.8321) (8303.1603 6625.9542)
    ))
    ; P0678 -- see feature_dimensions_mm.csv
    ("02_CORNICES" 0 (
      (8274.8092 6961.8321) (8274.8092 6625.9542)
    ))
    ; P0679 -- see feature_dimensions_mm.csv
    ("02_CORNICES" 0 (
      (8303.1603 6625.9542) (8274.8092 6625.9542)
    ))
    ; P0680 -- see feature_dimensions_mm.csv
    ("02_CORNICES" 0 (
      (8335.8779 6625.9542) (8303.1603 6625.9542)
    ))
    ; P0681 -- see feature_dimensions_mm.csv
    ("02_CORNICES" 0 (
      (8366.4122 6625.9542) (8335.8779 6625.9542)
    ))
    ; P0682 -- see feature_dimensions_mm.csv
    ("02_CORNICES" 0 (
      (8335.8779 6625.9542) (8335.8779 6961.8321) (8366.4122 6961.8321) (8366.4122 6625.9542)
    ))
    ; P0683 -- see feature_dimensions_mm.csv
    ("02_CORNICES" 0 (
      (8427.4809 6625.9542) (8366.4122 6625.9542)
    ))
    ; P0684 -- see feature_dimensions_mm.csv
    ("02_CORNICES" 0 (
      (8427.4809 6625.9542) (8427.4809 6961.8321)
    ))
    ; P0685 -- see feature_dimensions_mm.csv
    ("02_CORNICES" 0 (
      (8458.0153 6625.9542) (8427.4809 6625.9542)
    ))
    ; P0686 -- see feature_dimensions_mm.csv
    ("02_CORNICES" 0 (
      (8458.0153 6961.8321) (8458.0153 6625.9542)
    ))
    ; P0687 -- see feature_dimensions_mm.csv
    ("02_CORNICES" 0 (
      (8519.084 6625.9542) (8458.0153 6625.9542)
    ))
    ; P0688 -- see feature_dimensions_mm.csv
    ("02_CORNICES" 0 (
      (8519.084 6625.9542) (8519.084 6961.8321)
    ))
    ; P0689 -- see feature_dimensions_mm.csv
    ("02_CORNICES" 0 (
      (8549.6183 6625.9542) (8519.084 6625.9542)
    ))
    ; P0690 -- see feature_dimensions_mm.csv
    ("02_CORNICES" 0 (
      (8549.6183 6961.8321) (8549.6183 6625.9542)
    ))
    ; P0691 -- see feature_dimensions_mm.csv
    ("02_CORNICES" 0 (
      (8579.0687 6625.9542) (8549.6183 6625.9542)
    ))
    ; P0692 -- see feature_dimensions_mm.csv
    ("02_CORNICES" 0 (
      (8579.0687 6961.8321) (8579.0687 6625.9542)
    ))
    ; P0693 -- see feature_dimensions_mm.csv
    ("02_CORNICES" 0 (
      (8610.687 6625.9542) (8579.0687 6625.9542)
    ))
    ; P0694 -- see feature_dimensions_mm.csv
    ("02_CORNICES" 0 (
      (8610.687 6625.9542) (8610.687 6961.8321)
    ))
    ; P0695 -- see feature_dimensions_mm.csv
    ("02_CORNICES" 0 (
      (8641.2214 6625.9542) (8610.687 6625.9542)
    ))
    ; P0696 -- see feature_dimensions_mm.csv
    ("02_CORNICES" 0 (
      (8641.2214 6961.8321) (8641.2214 6625.9542)
    ))
    ; P0697 -- see feature_dimensions_mm.csv
    ("02_CORNICES" 0 (
      (8702.2901 6625.9542) (8671.7557 6625.9542) (8641.2214 6625.9542)
    ))
    ; P0698 -- see feature_dimensions_mm.csv
    ("02_CORNICES" 0 (
      (8687.0229 8320.6107) (8687.0229 8137.4046) (8671.7557 8137.4046)
    ))
    ; P0699 -- see feature_dimensions_mm.csv
    ("02_CORNICES" 0 (
      (8671.7557 7679.3893) (8671.7557 7740.458)
    ))
    ; P0700 -- see feature_dimensions_mm.csv
    ("02_CORNICES" 0 (
      (8671.7557 7374.0458) (8671.7557 7679.3893)
    ))
    ; P0701 -- see feature_dimensions_mm.csv
    ("02_CORNICES" 0 (
      (8671.7557 6961.8321) (8702.2901 6961.8321)
    ))
    ; P0702 -- see feature_dimensions_mm.csv
    ("02_CORNICES" 0 (
      (8702.2901 6961.8321) (8732.8244 6961.8321)
    ))
    ; P0703 -- see feature_dimensions_mm.csv
    ("02_CORNICES" 0 (
      (8702.2901 6625.9542) (8702.2901 6961.8321)
    ))
    ; P0704 -- see feature_dimensions_mm.csv
    ("02_CORNICES" 0 (
      (8732.8244 6625.9542) (8702.2901 6625.9542)
    ))
    ; P0705 -- see feature_dimensions_mm.csv
    ("02_CORNICES" 0 (
      (8732.8244 6961.8321) (8793.8931 6961.8321)
    ))
    ; P0706 -- see feature_dimensions_mm.csv
    ("02_CORNICES" 0 (
      (8732.8244 6961.8321) (8732.8244 6625.9542)
    ))
    ; P0707 -- see feature_dimensions_mm.csv
    ("02_CORNICES" 0 (
      (8793.8931 6625.9542) (8732.8244 6625.9542)
    ))
    ; P0708 -- see feature_dimensions_mm.csv
    ("02_CORNICES" 0 (
      (8793.8931 6961.8321) (8824.4275 6961.8321)
    ))
    ; P0709 -- see feature_dimensions_mm.csv
    ("02_CORNICES" 0 (
      (8793.8931 6625.9542) (8793.8931 6961.8321)
    ))
    ; P0710 -- see feature_dimensions_mm.csv
    ("02_CORNICES" 0 (
      (8824.4275 6625.9542) (8793.8931 6625.9542)
    ))
    ; P0711 -- see feature_dimensions_mm.csv
    ("02_CORNICES" 0 (
      (8824.4275 6961.8321) (8854.9618 6961.8321) (8854.9618 6625.9542)
    ))
    ; P0712 -- see feature_dimensions_mm.csv
    ("02_CORNICES" 0 (
      (8824.4275 6961.8321) (8824.4275 6625.9542)
    ))
    ; P0713 -- see feature_dimensions_mm.csv
    ("02_CORNICES" 0 (
      (8854.9618 6625.9542) (8824.4275 6625.9542)
    ))
    ; P0714 -- see feature_dimensions_mm.csv
    ("02_CORNICES" 0 (
      (14000.0 7740.458) (10122.1374 7740.458)
    ))
    ; P0715 -- see feature_dimensions_mm.csv
    ("02_CORNICES" 0 (
      (14000.0 7740.458) (13877.8626 7557.2519) (10244.2748 7557.2519) (10122.1374 7740.458)
    ))
    ; P0716 -- see feature_dimensions_mm.csv
    ("02_CORNICES" 0 (
      (10122.1374 7740.458) (10122.1374 7923.6641) (10122.1374 8076.3359) (10345.4656 8076.3359) (10369.8321 7996.9466)
      (10394.1985 7996.9466) (10414.5038 7877.8626) (10467.2824 7877.8626) (10487.5878 7996.9466) (10507.8931 7996.9466)
      (10528.1985 8076.3359) (10751.5267 8076.3359) (10775.8931 7996.9466) (10800.2595 7996.9466) (10820.5649 7877.8626)
      (10873.3435 7877.8626) (10893.6489 7996.9466) (10913.9542 7996.9466) (10934.2595 8076.3359) (11157.5878 8076.3359)
      (11181.9542 7996.9466) (11206.3206 7996.9466) (11226.6107 7877.8626) (11279.4046 7877.8626) (11299.7099 7996.9466)
      (11320.0153 7996.9466) (11340.3206 8076.3359) (11563.6489 8076.3359) (11588.0153 7996.9466) (11612.3664 7996.9466)
      (11632.6718 7877.8626) (11685.4656 7877.8626) (11705.771 7996.9466) (11726.0763 7996.9466) (11746.3664 8076.3359)
      (11969.7099 8076.3359) (11994.0763 7996.9466) (12018.4275 7996.9466) (12038.7328 7877.8626) (12091.5267 7877.8626)
      (12111.8321 7996.9466) (12132.1221 7996.9466) (12152.4275 8076.3359) (12375.771 8076.3359) (12400.1221 7996.9466)
      (12424.4885 7996.9466) (12444.7939 7877.8626) (12497.5878 7877.8626) (12517.8779 7996.9466) (12538.1832 7996.9466)
      (12558.4885 8076.3359) (12781.8168 8076.3359) (12806.1832 7996.9466) (12830.5496 7996.9466) (12850.855 7877.8626)
      (12903.6336 7877.8626) (12923.9389 7996.9466) (12944.2443 7996.9466) (12964.5496 8076.3359) (13187.8779 8076.3359)
      (13212.2443 7996.9466) (13236.6107 7996.9466) (13256.916 7877.8626) (13309.6947 7877.8626) (13330.0 7996.9466)
      (13350.3053 7996.9466) (13370.6107 8076.3359) (13593.9389 8076.3359) (13618.3053 7996.9466) (13642.6718 7996.9466)
      (13662.9771 7877.8626) (13715.7557 7877.8626) (13736.0611 7996.9466) (13756.3664 7996.9466) (13776.6718 8076.3359)
      (14000.0 8076.3359) (14000.0 7740.458)
    ))
    ; P0717 -- see feature_dimensions_mm.csv
    ("02_CORNICES" 0 (
      (10357.8931 6656.4885) (10290.0763 6656.4885) (10274.8092 6656.4885)
    ))
    ; P0718 -- see feature_dimensions_mm.csv
    ("02_CORNICES" 0 (
      (10290.0763 6564.8855) (10274.8092 6564.8855) (10274.8092 6656.4885)
    ))
    ; P0719 -- see feature_dimensions_mm.csv
    ("02_CORNICES" 0 (
      (10274.8092 6656.4885) (10274.8092 6977.0992) (10290.0763 6977.0992) (10357.8931 6977.0992)
    ))
    ; P0720 -- see feature_dimensions_mm.csv
    ("02_CORNICES" 0 (
      (10335.8779 3633.5878) (10290.0763 3633.5878) (10274.8092 3633.5878)
    ))
    ; P0721 -- see feature_dimensions_mm.csv
    ("02_CORNICES" 0 (
      (10274.8092 3633.5878) (10274.8092 3618.3206) (10335.8779 3618.3206)
    ))
    ; P0722 -- see feature_dimensions_mm.csv
    ("02_CORNICES" 0 (
      (10290.0763 3740.458) (10259.542 3740.458) (10259.542 3633.5878) (10274.8092 3633.5878)
    ))
    ; P0723 -- see feature_dimensions_mm.csv
    ("02_CORNICES" 0 (
      (10687.0229 3633.5878) (10335.8779 3633.5878)
    ))
    ; P0724 -- see feature_dimensions_mm.csv
    ("02_CORNICES" 0 (
      (10335.8779 3633.5878) (10335.8779 3618.3206)
    ))
    ; P0725 -- see feature_dimensions_mm.csv
    ("02_CORNICES" 0 (
      (10717.5573 3679.3893) (10687.0229 3679.3893) (10335.8779 3679.3893) (10335.8779 3664.1221) (10335.8779 3633.5878)
    ))
    ; P0726 -- see feature_dimensions_mm.csv
    ("02_CORNICES" 0 (
      (10335.8779 3618.3206) (10519.084 3618.3206) (13938.9313 3618.3206) (13938.9313 3633.5878)
    ))
    ; P0727 -- see feature_dimensions_mm.csv
    ("02_CORNICES" 0 (
      (10357.8931 6977.0992) (10440.9771 6977.0992)
    ))
    ; P0728 -- see feature_dimensions_mm.csv
    ("02_CORNICES" 0 (
      (10357.8931 6977.0992) (10357.8931 6656.4885)
    ))
    ; P0729 -- see feature_dimensions_mm.csv
    ("02_CORNICES" 0 (
      (10440.9771 6656.4885) (10357.8931 6656.4885)
    ))
    ; P0730 -- see feature_dimensions_mm.csv
    ("02_CORNICES" 0 (
      (10440.9771 6977.0992) (10524.0611 6977.0992)
    ))
    ; P0731 -- see feature_dimensions_mm.csv
    ("02_CORNICES" 0 (
      (10440.9771 6977.0992) (10440.9771 6656.4885)
    ))
    ; P0732 -- see feature_dimensions_mm.csv
    ("02_CORNICES" 0 (
      (10524.0611 6656.4885) (10440.9771 6656.4885)
    ))
    ; P0733 -- see feature_dimensions_mm.csv
    ("02_CORNICES" 0 (
      (13961.8321 3389.313) (10519.084 3389.313)
    ))
    ; P0734 -- see feature_dimensions_mm.csv
    ("02_CORNICES" 0 (
      (10519.084 3297.7099) (13893.1298 3297.7099) (13961.8321 3389.313)
    ))
    ; P0735 -- see feature_dimensions_mm.csv
    ("02_CORNICES" 0 (
      (10519.084 3282.4427) (13969.4656 3282.4427) (13969.4656 3389.313) (13961.8321 3389.313)
    ))
    ; P0736 -- see feature_dimensions_mm.csv
    ("02_CORNICES" 0 (
      (10524.0611 6977.0992) (10607.1298 6977.0992)
    ))
    ; P0737 -- see feature_dimensions_mm.csv
    ("02_CORNICES" 0 (
      (10524.0611 6977.0992) (10524.0611 6656.4885)
    ))
    ; P0738 -- see feature_dimensions_mm.csv
    ("02_CORNICES" 0 (
      (10607.1298 6656.4885) (10524.0611 6656.4885)
    ))
    ; P0739 -- see feature_dimensions_mm.csv
    ("02_CORNICES" 0 (
      (10607.1298 6977.0992) (10690.2137 6977.0992)
    ))
    ; P0740 -- see feature_dimensions_mm.csv
    ("02_CORNICES" 0 (
      (10607.1298 6977.0992) (10607.1298 6656.4885)
    ))
    ; P0741 -- see feature_dimensions_mm.csv
    ("02_CORNICES" 0 (
      (10690.2137 6656.4885) (10607.1298 6656.4885)
    ))
    ; P0742 -- see feature_dimensions_mm.csv
    ("02_CORNICES" 0 (
      (10717.5573 3679.3893) (10717.5573 3740.458) (10687.0229 3740.458)
    ))
    ; P0743 -- see feature_dimensions_mm.csv
    ("02_CORNICES" 0 (
      (10690.2137 6977.0992) (10773.2977 6977.0992)
    ))
    ; P0744 -- see feature_dimensions_mm.csv
    ("02_CORNICES" 0 (
      (10690.2137 6977.0992) (10690.2137 6656.4885)
    ))
    ; P0745 -- see feature_dimensions_mm.csv
    ("02_CORNICES" 0 (
      (10773.2977 6656.4885) (10690.2137 6656.4885)
    ))
    ; P0746 -- see feature_dimensions_mm.csv
    ("02_CORNICES" 0 (
      (13404.5802 3679.3893) (13068.7023 3679.3893) (11053.4351 3679.3893) (10717.5573 3679.3893)
    ))
    ; P0747 -- see feature_dimensions_mm.csv
    ("02_CORNICES" 0 (
      (10717.5573 3633.5878) (10717.5573 3679.3893)
    ))
    ; P0748 -- see feature_dimensions_mm.csv
    ("02_CORNICES" 0 (
      (10773.2977 6977.0992) (10856.3817 6977.0992)
    ))
    ; P0749 -- see feature_dimensions_mm.csv
    ("02_CORNICES" 0 (
      (10773.2977 6977.0992) (10773.2977 6656.4885)
    ))
    ; P0750 -- see feature_dimensions_mm.csv
    ("02_CORNICES" 0 (
      (10856.3817 6656.4885) (10773.2977 6656.4885)
    ))
    ; P0751 -- see feature_dimensions_mm.csv
    ("02_CORNICES" 0 (
      (10885.4962 2061.0687) (10850.3206 2061.0687) (10783.6489 2061.0687)
    ))
    ; P0752 -- see feature_dimensions_mm.csv
    ("02_CORNICES" 0 (
      (10809.1603 1862.5954) (10809.1603 1865.0382) (10809.1603 1969.4656) (10825.4809 1989.0534)
    ))
    ; P0753 -- see feature_dimensions_mm.csv
    ("02_CORNICES" 0 (
      (10856.3817 6977.0992) (10939.4656 6977.0992)
    ))
    ; P0754 -- see feature_dimensions_mm.csv
    ("02_CORNICES" 0 (
      (10856.3817 6977.0992) (10856.3817 6656.4885)
    ))
    ; P0755 -- see feature_dimensions_mm.csv
    ("02_CORNICES" 0 (
      (10939.4656 6656.4885) (10856.3817 6656.4885)
    ))
    ; P0756 -- see feature_dimensions_mm.csv
    ("02_CORNICES" 0 (
      (10939.4656 6977.0992) (11022.5496 6977.0992)
    ))
    ; P0757 -- see feature_dimensions_mm.csv
    ("02_CORNICES" 0 (
      (10939.4656 6977.0992) (10939.4656 6656.4885)
    ))
    ; P0758 -- see feature_dimensions_mm.csv
    ("02_CORNICES" 0 (
      (11022.5496 6656.4885) (10939.4656 6656.4885)
    ))
    ; P0759 -- see feature_dimensions_mm.csv
    ("02_CORNICES" 0 (
      (11022.5496 6977.0992) (11105.6336 6977.0992)
    ))
    ; P0760 -- see feature_dimensions_mm.csv
    ("02_CORNICES" 0 (
      (11022.5496 6977.0992) (11022.5496 6656.4885)
    ))
    ; P0761 -- see feature_dimensions_mm.csv
    ("02_CORNICES" 0 (
      (11105.6336 6656.4885) (11022.5496 6656.4885)
    ))
    ; P0762 -- see feature_dimensions_mm.csv
    ("02_CORNICES" 0 (
      (13068.7023 3633.5878) (11053.4351 3633.5878)
    ))
    ; P0763 -- see feature_dimensions_mm.csv
    ("02_CORNICES" 0 (
      (11105.6336 6977.0992) (11188.7023 6977.0992)
    ))
    ; P0764 -- see feature_dimensions_mm.csv
    ("02_CORNICES" 0 (
      (11105.6336 6977.0992) (11105.6336 6656.4885)
    ))
    ; P0765 -- see feature_dimensions_mm.csv
    ("02_CORNICES" 0 (
      (11188.7023 6656.4885) (11105.6336 6656.4885)
    ))
    ; P0766 -- see feature_dimensions_mm.csv
    ("02_CORNICES" 0 (
      (11188.7023 6977.0992) (11271.7863 6977.0992)
    ))
    ; P0767 -- see feature_dimensions_mm.csv
    ("02_CORNICES" 0 (
      (11188.7023 6977.0992) (11188.7023 6656.4885)
    ))
    ; P0768 -- see feature_dimensions_mm.csv
    ("02_CORNICES" 0 (
      (11271.7863 6656.4885) (11188.7023 6656.4885)
    ))
    ; P0769 -- see feature_dimensions_mm.csv
    ("02_CORNICES" 0 (
      (11261.4962 2373.2977) (11249.4351 2433.2366) (11213.7405 2610.687)
    ))
    ; P0770 -- see feature_dimensions_mm.csv
    ("02_CORNICES" 0 (
      (11451.6031 2351.145) (11265.9542 2351.145)
    ))
    ; P0771 -- see feature_dimensions_mm.csv
    ("02_CORNICES" 0 (
      (11271.7863 6977.0992) (11354.8702 6977.0992)
    ))
    ; P0772 -- see feature_dimensions_mm.csv
    ("02_CORNICES" 0 (
      (11271.7863 6977.0992) (11271.7863 6656.4885)
    ))
    ; P0773 -- see feature_dimensions_mm.csv
    ("02_CORNICES" 0 (
      (11354.8702 6656.4885) (11271.7863 6656.4885)
    ))
    ; P0774 -- see feature_dimensions_mm.csv
    ("02_CORNICES" 0 (
      (11354.8702 6977.0992) (11437.9542 6977.0992)
    ))
    ; P0775 -- see feature_dimensions_mm.csv
    ("02_CORNICES" 0 (
      (11354.8702 6977.0992) (11354.8702 6656.4885)
    ))
    ; P0776 -- see feature_dimensions_mm.csv
    ("02_CORNICES" 0 (
      (11437.9542 6656.4885) (11354.8702 6656.4885)
    ))
    ; P0777 -- see feature_dimensions_mm.csv
    ("02_CORNICES" 0 (
      (11437.9542 6977.0992) (11521.0382 6977.0992)
    ))
    ; P0778 -- see feature_dimensions_mm.csv
    ("02_CORNICES" 0 (
      (11437.9542 6977.0992) (11437.9542 6656.4885)
    ))
    ; P0779 -- see feature_dimensions_mm.csv
    ("02_CORNICES" 0 (
      (11521.0382 6656.4885) (11437.9542 6656.4885)
    ))
    ; P0780 -- see feature_dimensions_mm.csv
    ("02_CORNICES" 0 (
      (11503.8168 2610.687) (11468.1221 2433.2366) (11456.0611 2373.2977)
    ))
    ; P0781 -- see feature_dimensions_mm.csv
    ("02_CORNICES" 0 (
      (11521.0382 6977.0992) (11604.1221 6977.0992)
    ))
    ; P0782 -- see feature_dimensions_mm.csv
    ("02_CORNICES" 0 (
      (11521.0382 6977.0992) (11521.0382 6656.4885)
    ))
    ; P0783 -- see feature_dimensions_mm.csv
    ("02_CORNICES" 0 (
      (11604.1221 6656.4885) (11521.0382 6656.4885)
    ))
    ; P0784 -- see feature_dimensions_mm.csv
    ("02_CORNICES" 0 (
      (11604.1221 6977.0992) (11687.2061 6977.0992)
    ))
    ; P0785 -- see feature_dimensions_mm.csv
    ("02_CORNICES" 0 (
      (11604.1221 6977.0992) (11604.1221 6656.4885)
    ))
    ; P0786 -- see feature_dimensions_mm.csv
    ("02_CORNICES" 0 (
      (11687.2061 6656.4885) (11604.1221 6656.4885)
    ))
    ; P0787 -- see feature_dimensions_mm.csv
    ("02_CORNICES" 0 (
      (11687.2061 6977.0992) (11770.2748 6977.0992)
    ))
    ; P0788 -- see feature_dimensions_mm.csv
    ("02_CORNICES" 0 (
      (11687.2061 6977.0992) (11687.2061 6656.4885)
    ))
    ; P0789 -- see feature_dimensions_mm.csv
    ("02_CORNICES" 0 (
      (11770.2748 6656.4885) (11687.2061 6656.4885)
    ))
    ; P0790 -- see feature_dimensions_mm.csv
    ("02_CORNICES" 0 (
      (11770.2748 6977.0992) (11853.3588 6977.0992)
    ))
    ; P0791 -- see feature_dimensions_mm.csv
    ("02_CORNICES" 0 (
      (11770.2748 6977.0992) (11770.2748 6656.4885)
    ))
    ; P0792 -- see feature_dimensions_mm.csv
    ("02_CORNICES" 0 (
      (11853.3588 6656.4885) (11770.2748 6656.4885)
    ))
    ; P0793 -- see feature_dimensions_mm.csv
    ("02_CORNICES" 0 (
      (11853.3588 6977.0992) (11936.4427 6977.0992)
    ))
    ; P0794 -- see feature_dimensions_mm.csv
    ("02_CORNICES" 0 (
      (11853.3588 6977.0992) (11853.3588 6656.4885)
    ))
    ; P0795 -- see feature_dimensions_mm.csv
    ("02_CORNICES" 0 (
      (11936.4427 6656.4885) (11853.3588 6656.4885)
    ))
    ; P0796 -- see feature_dimensions_mm.csv
    ("02_CORNICES" 0 (
      (11936.4427 6977.0992) (12019.5267 6977.0992)
    ))
    ; P0797 -- see feature_dimensions_mm.csv
    ("02_CORNICES" 0 (
      (11936.4427 6977.0992) (11936.4427 6656.4885)
    ))
    ; P0798 -- see feature_dimensions_mm.csv
    ("02_CORNICES" 0 (
      (12019.5267 6656.4885) (11936.4427 6656.4885)
    ))
    ; P0799 -- see feature_dimensions_mm.csv
    ("02_CORNICES" 0 (
      (11947.6489 5938.9313) (11908.3969 5938.9313) (11941.4198 5782.9924) (11963.3588 5679.3893)
    ))
    ; P0800 -- see feature_dimensions_mm.csv
    ("02_CORNICES" 0 (
      (12158.7786 5679.3893) (12180.7176 5782.9924) (12213.7405 5938.9313) (12167.0076 5938.9313) (12140.458 5938.9313)
      (12116.0305 5938.9313) (12088.5496 5938.9313) (12061.0687 5938.9313) (12033.5878 5938.9313) (12006.1069 5938.9313)
      (11981.6794 5938.9313)
    ))
    ; P0801 -- see feature_dimensions_mm.csv
    ("02_CORNICES" 0 (
      (12127.1603 2061.0687) (12193.8321 2061.0687) (12262.4733 2061.0687) (12274.8092 2061.0687) (12247.2977 2028.0611)
      (12198.4733 1969.4656) (12198.4733 1862.5954) (12000.0 1862.5954)
    ))
    ; P0802 -- see feature_dimensions_mm.csv
    ("02_CORNICES" 0 (
      (12019.5267 6977.0992) (12102.6107 6977.0992)
    ))
    ; P0803 -- see feature_dimensions_mm.csv
    ("02_CORNICES" 0 (
      (12019.5267 6977.0992) (12019.5267 6656.4885)
    ))
    ; P0804 -- see feature_dimensions_mm.csv
    ("02_CORNICES" 0 (
      (12102.6107 6656.4885) (12019.5267 6656.4885)
    ))
    ; P0805 -- see feature_dimensions_mm.csv
    ("02_CORNICES" 0 (
      (12102.6107 6977.0992) (12185.6947 6977.0992)
    ))
    ; P0806 -- see feature_dimensions_mm.csv
    ("02_CORNICES" 0 (
      (12102.6107 6977.0992) (12102.6107 6656.4885)
    ))
    ; P0807 -- see feature_dimensions_mm.csv
    ("02_CORNICES" 0 (
      (12185.6947 6656.4885) (12102.6107 6656.4885)
    ))
    ; P0808 -- see feature_dimensions_mm.csv
    ("02_CORNICES" 0 (
      (12185.6947 6977.0992) (12268.7786 6977.0992)
    ))
    ; P0809 -- see feature_dimensions_mm.csv
    ("02_CORNICES" 0 (
      (12185.6947 6977.0992) (12185.6947 6656.4885)
    ))
    ; P0810 -- see feature_dimensions_mm.csv
    ("02_CORNICES" 0 (
      (12268.7786 6656.4885) (12185.6947 6656.4885)
    ))
    ; P0811 -- see feature_dimensions_mm.csv
    ("02_CORNICES" 0 (
      (12268.7786 6977.0992) (12351.8626 6977.0992)
    ))
    ; P0812 -- see feature_dimensions_mm.csv
    ("02_CORNICES" 0 (
      (12268.7786 6977.0992) (12268.7786 6656.4885)
    ))
    ; P0813 -- see feature_dimensions_mm.csv
    ("02_CORNICES" 0 (
      (12351.8626 6656.4885) (12268.7786 6656.4885)
    ))
    ; P0814 -- see feature_dimensions_mm.csv
    ("02_CORNICES" 0 (
      (12351.8626 6977.0992) (12434.9313 6977.0992)
    ))
    ; P0815 -- see feature_dimensions_mm.csv
    ("02_CORNICES" 0 (
      (12351.8626 6977.0992) (12351.8626 6656.4885)
    ))
    ; P0816 -- see feature_dimensions_mm.csv
    ("02_CORNICES" 0 (
      (12434.9313 6656.4885) (12351.8626 6656.4885)
    ))
    ; P0817 -- see feature_dimensions_mm.csv
    ("02_CORNICES" 0 (
      (12434.9313 6977.0992) (12518.0153 6977.0992)
    ))
    ; P0818 -- see feature_dimensions_mm.csv
    ("02_CORNICES" 0 (
      (12434.9313 6977.0992) (12434.9313 6656.4885)
    ))
    ; P0819 -- see feature_dimensions_mm.csv
    ("02_CORNICES" 0 (
      (12518.0153 6656.4885) (12434.9313 6656.4885)
    ))
    ; P0820 -- see feature_dimensions_mm.csv
    ("02_CORNICES" 0 (
      (12518.0153 6977.0992) (12601.0992 6977.0992)
    ))
    ; P0821 -- see feature_dimensions_mm.csv
    ("02_CORNICES" 0 (
      (12518.0153 6977.0992) (12518.0153 6656.4885)
    ))
    ; P0822 -- see feature_dimensions_mm.csv
    ("02_CORNICES" 0 (
      (12601.0992 6656.4885) (12518.0153 6656.4885)
    ))
    ; P0823 -- see feature_dimensions_mm.csv
    ("02_CORNICES" 0 (
      (12605.0076 2373.2977) (12592.9466 2433.2366) (12557.2519 2610.687)
    ))
    ; P0824 -- see feature_dimensions_mm.csv
    ("02_CORNICES" 0 (
      (12601.0992 6977.0992) (12684.1832 6977.0992)
    ))
    ; P0825 -- see feature_dimensions_mm.csv
    ("02_CORNICES" 0 (
      (12601.0992 6977.0992) (12601.0992 6656.4885)
    ))
    ; P0826 -- see feature_dimensions_mm.csv
    ("02_CORNICES" 0 (
      (12684.1832 6656.4885) (12601.0992 6656.4885)
    ))
    ; P0827 -- see feature_dimensions_mm.csv
    ("02_CORNICES" 0 (
      (12684.1832 6977.0992) (12767.2672 6977.0992)
    ))
    ; P0828 -- see feature_dimensions_mm.csv
    ("02_CORNICES" 0 (
      (12684.1832 6977.0992) (12684.1832 6656.4885)
    ))
    ; P0829 -- see feature_dimensions_mm.csv
    ("02_CORNICES" 0 (
      (12767.2672 6656.4885) (12684.1832 6656.4885)
    ))
    ; P0830 -- see feature_dimensions_mm.csv
    ("02_CORNICES" 0 (
      (12767.2672 6977.0992) (12850.3511 6977.0992)
    ))
    ; P0831 -- see feature_dimensions_mm.csv
    ("02_CORNICES" 0 (
      (12767.2672 6977.0992) (12767.2672 6656.4885)
    ))
    ; P0832 -- see feature_dimensions_mm.csv
    ("02_CORNICES" 0 (
      (12850.3511 6656.4885) (12767.2672 6656.4885)
    ))
    ; P0833 -- see feature_dimensions_mm.csv
    ("02_CORNICES" 0 (
      (12847.3282 2610.687) (12811.6336 2433.2366) (12799.5725 2373.2977)
    ))
    ; P0834 -- see feature_dimensions_mm.csv
    ("02_CORNICES" 0 (
      (12850.3511 6977.0992) (12933.4351 6977.0992)
    ))
    ; P0835 -- see feature_dimensions_mm.csv
    ("02_CORNICES" 0 (
      (12850.3511 6977.0992) (12850.3511 6656.4885)
    ))
    ; P0836 -- see feature_dimensions_mm.csv
    ("02_CORNICES" 0 (
      (12933.4351 6656.4885) (12850.3511 6656.4885)
    ))
    ; P0837 -- see feature_dimensions_mm.csv
    ("02_CORNICES" 0 (
      (12933.4351 6977.0992) (13016.5038 6977.0992)
    ))
    ; P0838 -- see feature_dimensions_mm.csv
    ("02_CORNICES" 0 (
      (12933.4351 6977.0992) (12933.4351 6656.4885)
    ))
    ; P0839 -- see feature_dimensions_mm.csv
    ("02_CORNICES" 0 (
      (13016.5038 6656.4885) (12933.4351 6656.4885)
    ))
    ; P0840 -- see feature_dimensions_mm.csv
    ("02_CORNICES" 0 (
      (13016.5038 6977.0992) (13099.5878 6977.0992)
    ))
    ; P0841 -- see feature_dimensions_mm.csv
    ("02_CORNICES" 0 (
      (13016.5038 6977.0992) (13016.5038 6656.4885)
    ))
    ; P0842 -- see feature_dimensions_mm.csv
    ("02_CORNICES" 0 (
      (13099.5878 6656.4885) (13016.5038 6656.4885)
    ))
    ; P0843 -- see feature_dimensions_mm.csv
    ("02_CORNICES" 0 (
      (13099.5878 6977.0992) (13182.6718 6977.0992)
    ))
    ; P0844 -- see feature_dimensions_mm.csv
    ("02_CORNICES" 0 (
      (13099.5878 6977.0992) (13099.5878 6656.4885)
    ))
    ; P0845 -- see feature_dimensions_mm.csv
    ("02_CORNICES" 0 (
      (13182.6718 6656.4885) (13099.5878 6656.4885)
    ))
    ; P0846 -- see feature_dimensions_mm.csv
    ("02_CORNICES" 0 (
      (13182.6718 6977.0992) (13265.7557 6977.0992)
    ))
    ; P0847 -- see feature_dimensions_mm.csv
    ("02_CORNICES" 0 (
      (13182.6718 6977.0992) (13182.6718 6656.4885)
    ))
    ; P0848 -- see feature_dimensions_mm.csv
    ("02_CORNICES" 0 (
      (13265.7557 6656.4885) (13182.6718 6656.4885)
    ))
    ; P0849 -- see feature_dimensions_mm.csv
    ("02_CORNICES" 0 (
      (13265.7557 6977.0992) (13348.8397 6977.0992)
    ))
    ; P0850 -- see feature_dimensions_mm.csv
    ("02_CORNICES" 0 (
      (13265.7557 6977.0992) (13265.7557 6656.4885)
    ))
    ; P0851 -- see feature_dimensions_mm.csv
    ("02_CORNICES" 0 (
      (13348.8397 6656.4885) (13265.7557 6656.4885)
    ))
    ; P0852 -- see feature_dimensions_mm.csv
    ("02_CORNICES" 0 (
      (13389.313 1862.5954) (13343.5115 1969.4656)
    ))
    ; P0853 -- see feature_dimensions_mm.csv
    ("02_CORNICES" 0 (
      (13348.8397 6977.0992) (13431.9237 6977.0992)
    ))
    ; P0854 -- see feature_dimensions_mm.csv
    ("02_CORNICES" 0 (
      (13348.8397 6977.0992) (13348.8397 6656.4885)
    ))
    ; P0855 -- see feature_dimensions_mm.csv
    ("02_CORNICES" 0 (
      (13431.9237 6656.4885) (13348.8397 6656.4885)
    ))
    ; P0856 -- see feature_dimensions_mm.csv
    ("02_CORNICES" 0 (
      (13862.5954 3679.3893) (13435.1145 3679.3893) (13404.5802 3679.3893)
    ))
    ; P0857 -- see feature_dimensions_mm.csv
    ("02_CORNICES" 0 (
      (13404.5802 3679.3893) (13404.5802 3633.5878)
    ))
    ; P0858 -- see feature_dimensions_mm.csv
    ("02_CORNICES" 0 (
      (13435.1145 3740.458) (13404.5802 3740.458) (13404.5802 3679.3893)
    ))
    ; P0859 -- see feature_dimensions_mm.csv
    ("02_CORNICES" 0 (
      (13431.9237 6977.0992) (13515.0076 6977.0992)
    ))
    ; P0860 -- see feature_dimensions_mm.csv
    ("02_CORNICES" 0 (
      (13431.9237 6977.0992) (13431.9237 6656.4885)
    ))
    ; P0861 -- see feature_dimensions_mm.csv
    ("02_CORNICES" 0 (
      (13515.0076 6656.4885) (13431.9237 6656.4885)
    ))
    ; P0862 -- see feature_dimensions_mm.csv
    ("02_CORNICES" 0 (
      (13862.5954 3633.5878) (13832.0611 3633.5878) (13435.1145 3633.5878)
    ))
    ; P0863 -- see feature_dimensions_mm.csv
    ("02_CORNICES" 0 (
      (13515.0076 6977.0992) (13598.0763 6977.0992)
    ))
    ; P0864 -- see feature_dimensions_mm.csv
    ("02_CORNICES" 0 (
      (13515.0076 6977.0992) (13515.0076 6656.4885)
    ))
    ; P0865 -- see feature_dimensions_mm.csv
    ("02_CORNICES" 0 (
      (13598.0763 6656.4885) (13515.0076 6656.4885)
    ))
    ; P0866 -- see feature_dimensions_mm.csv
    ("02_CORNICES" 0 (
      (13598.0763 6977.0992) (13681.1603 6977.0992)
    ))
    ; P0867 -- see feature_dimensions_mm.csv
    ("02_CORNICES" 0 (
      (13598.0763 6977.0992) (13598.0763 6656.4885)
    ))
    ; P0868 -- see feature_dimensions_mm.csv
    ("02_CORNICES" 0 (
      (13681.1603 6656.4885) (13598.0763 6656.4885)
    ))
    ; P0869 -- see feature_dimensions_mm.csv
    ("02_CORNICES" 0 (
      (13681.1603 6977.0992) (13764.2443 6977.0992)
    ))
    ; P0870 -- see feature_dimensions_mm.csv
    ("02_CORNICES" 0 (
      (13681.1603 6977.0992) (13681.1603 6656.4885)
    ))
    ; P0871 -- see feature_dimensions_mm.csv
    ("02_CORNICES" 0 (
      (13764.2443 6656.4885) (13681.1603 6656.4885)
    ))
    ; P0872 -- see feature_dimensions_mm.csv
    ("02_CORNICES" 0 (
      (13725.1908 1969.4656) (13725.1908 1862.5954)
    ))
    ; P0873 -- see feature_dimensions_mm.csv
    ("02_CORNICES" 0 (
      (13764.2443 6977.0992) (13832.0611 6977.0992) (13847.3282 6977.0992) (13847.3282 6656.4885)
    ))
    ; P0874 -- see feature_dimensions_mm.csv
    ("02_CORNICES" 0 (
      (13764.2443 6977.0992) (13764.2443 6656.4885)
    ))
    ; P0875 -- see feature_dimensions_mm.csv
    ("02_CORNICES" 0 (
      (13847.3282 6656.4885) (13832.0611 6656.4885) (13764.2443 6656.4885)
    ))
    ; P0876 -- see feature_dimensions_mm.csv
    ("02_CORNICES" 0 (
      (13847.3282 6656.4885) (13847.3282 6564.8855) (13832.0611 6564.8855)
    ))
    ; P0877 -- see feature_dimensions_mm.csv
    ("02_CORNICES" 0 (
      (13862.5954 3679.3893) (13862.5954 3740.458) (13832.0611 3740.458)
    ))
    ; P0878 -- see feature_dimensions_mm.csv
    ("02_CORNICES" 0 (
      (13938.9313 3633.5878) (13938.9313 3679.3893) (13862.5954 3679.3893)
    ))
    ; P0879 -- see feature_dimensions_mm.csv
    ("02_CORNICES" 0 (
      (13862.5954 3633.5878) (13862.5954 3679.3893)
    ))
    ; P0880 -- see feature_dimensions_mm.csv
    ("02_CORNICES" 0 (
      (13938.9313 3633.5878) (13862.5954 3633.5878)
    ))
    ; P0881 -- see feature_dimensions_mm.csv
    ("02_CORNICES" 0 (
      (13961.8321 3389.313) (13984.7328 3419.8473) (14000.0 3633.5878) (13938.9313 3633.5878)
    ))
    ; P0882 -- see feature_dimensions_mm.csv
    ("02_CORNICES" 1 (
      (2151.7863 2580.1527) (2191.7252 2381.6794) (2327.3588 2381.6794) (2367.2977 2580.1527)
    ))
    ; P0883 -- see feature_dimensions_mm.csv
    ("02_CORNICES" 1 (
      (2862.1069 5908.3969) (2904.1374 5709.9237) (3050.0611 5709.9237) (3092.0916 5908.3969)
    ))
    ; P0884 -- see feature_dimensions_mm.csv
    ("02_CORNICES" 1 (
      (3579.7405 2595.4198) (3618.9008 2412.2137) (3755.145 2412.2137) (3794.3053 2595.4198)
    ))
    ; P0885 -- see feature_dimensions_mm.csv
    ("02_CORNICES" 1 (
      (9395.6794 2610.687) (9433.5115 2412.2137) (9558.855 2412.2137) (9596.687 2610.687)
    ))
    ; P0886 -- see feature_dimensions_mm.csv
    ("02_CORNICES" 1 (
      (11251.0229 2580.1527) (11290.9618 2381.6794) (11426.5954 2381.6794) (11466.5344 2580.1527)
    ))
    ; P0887 -- see feature_dimensions_mm.csv
    ("02_CORNICES" 1 (
      (11946.0763 5908.3969) (11988.1069 5709.9237) (12134.0305 5709.9237) (12176.0611 5908.3969)
    ))
    ; P0888 -- see feature_dimensions_mm.csv
    ("02_CORNICES" 1 (
      (12594.5344 2580.1527) (12634.4733 2381.6794) (12770.1069 2381.6794) (12810.0458 2580.1527)
    ))
    ; P0889 -- see feature_dimensions_mm.csv
    ("03_FRAMES_DOORS" 0 (
      (1404.5802 9236.6412) (1404.5802 8946.5649) (1206.1069 8946.5649) (1206.1069 9236.6412)
    ))
    ; P0890 -- see feature_dimensions_mm.csv
    ("03_FRAMES_DOORS" 0 (
      (1435.1145 1282.4427) (1435.1145 931.2977) (1435.1145 656.4885) (1648.855 656.4885) (1709.9237 656.4885)
    ))
    ; P0891 -- see feature_dimensions_mm.csv
    ("03_FRAMES_DOORS" 0 (
      (1862.5954 8946.5649) (1694.6565 8946.5649) (1694.6565 8992.3664) (1694.6565 9083.9695) (1694.6565 9160.3053)
    ))
    ; P0892 -- see feature_dimensions_mm.csv
    ("03_FRAMES_DOORS" 0 (
      (1709.9237 1862.5954) (1709.9237 656.4885)
    ))
    ; P0893 -- see feature_dimensions_mm.csv
    ("03_FRAMES_DOORS" 0 (
      (1711.8321 2122.5954) (1695.3435 2088.3817) (1684.4122 2061.0687) (1740.458 2061.0687) (1664.1221 1969.4656)
      (1664.1221 1862.5954) (1709.9237 1862.5954)
    ))
    ; P0894 -- see feature_dimensions_mm.csv
    ("03_FRAMES_DOORS" 0 (
      (2809.1603 656.4885) (2809.1603 1865.0382) (2807.9847 1898.8244) (2804.458 1932.4733) (2798.5954 1965.8321)
      (2790.4275 1998.7481) (2779.9847 2031.1145) (2767.3282 2062.7481) (2752.4733 2093.542) (2735.5267 2123.3588)
      (2716.5344 2152.0611) (2695.5878 2179.542) (2672.7634 2205.6794) (2648.1832 2230.3511) (2621.9237 2253.4656)
      (2594.1221 2274.916) (2564.9008 2294.6107) (2534.3511 2312.458) (2502.626 2328.3969) (2469.8779 2342.3511)
      (2436.2137 2354.2595) (2401.7863 2364.0763) (2366.7634 2371.7557) (2356.8244 2373.2977) (2352.3664 2351.145)
      (2166.7176 2351.145) (2162.2595 2373.2977) (2152.3206 2371.7557) (2117.2977 2364.0763) (2082.8702 2354.2595)
      (2049.2061 2342.3511) (2016.458 2328.3969) (1984.7328 2312.458) (1954.1832 2294.6107) (1924.9618 2274.916)
      (1897.1603 2253.4656) (1870.9008 2230.3511) (1846.3206 2205.6794) (1823.4962 2179.542) (1802.5496 2152.0611)
      (1783.5573 2123.3588) (1766.6107 2093.542) (1751.7557 2062.7481) (1739.0992 2031.1145) (1728.6565 1998.7481)
      (1720.4885 1965.8321) (1714.626 1932.4733) (1711.0992 1898.8244) (1709.9237 1865.0382) (1709.9237 1862.5954)
    ))
    ; P0895 -- see feature_dimensions_mm.csv
    ("03_FRAMES_DOORS" 0 (
      (1709.9237 656.4885) (1770.9924 656.4885)
    ))
    ; P0896 -- see feature_dimensions_mm.csv
    ("03_FRAMES_DOORS" 0 (
      (1800.3969 2247.1908) (1775.0534 2218.1527) (1751.771 2187.6183) (1730.6718 2155.7252)
    ))
    ; P0897 -- see feature_dimensions_mm.csv
    ("03_FRAMES_DOORS" 0 (
      (1770.9924 656.4885) (2748.0916 656.4885)
    ))
    ; P0898 -- see feature_dimensions_mm.csv
    ("03_FRAMES_DOORS" 0 (
      (1770.9924 656.4885) (1770.9924 1861.374) (1772.0458 1891.4046) (1775.1756 1921.313) (1780.3817 1950.9618)
      (1787.6336 1980.229) (1796.916 2008.9924) (1808.1832 2037.1145) (1821.374 2064.4885) (1836.4427 2090.9924)
      (1853.3282 2116.5191) (1871.9542 2140.9466) (1892.229 2164.1679) (1914.0916 2186.1069) (1937.4198 2206.6412)
      (1962.1374 2225.7099) (1988.1221 2243.2214) (2015.2672 2259.084) (2043.4656 2273.2519) (2072.5802 2285.6489)
      (2102.5038 2296.2443) (2133.0992 2304.9618) (2164.229 2311.7863) (2195.771 2316.687) (2227.5878 2319.6336)
      (2259.542 2320.6107) (2291.4962 2319.6336) (2323.313 2316.687) (2354.855 2311.7863) (2385.9847 2304.9618)
      (2416.5802 2296.2443) (2446.5038 2285.6489) (2475.6183 2273.2519) (2503.8168 2259.084) (2530.9618 2243.2214)
      (2556.9466 2225.7099) (2581.6641 2206.6412) (2604.9924 2186.1069) (2626.855 2164.1679) (2647.1298 2140.9466)
      (2665.7557 2116.5191) (2682.6412 2090.9924) (2697.7099 2064.4885) (2710.9008 2037.1145) (2722.1679 2008.9924)
      (2731.4504 1980.229) (2738.7023 1950.9618) (2743.9084 1921.313) (2747.0382 1891.4046) (2748.0916 1861.374)
      (2748.0916 656.4885)
    ))
    ; P0899 -- see feature_dimensions_mm.csv
    ("03_FRAMES_DOORS" 0 (
      (1856.8855 2300.2901) (1827.7252 2274.6107)
    ))
    ; P0900 -- see feature_dimensions_mm.csv
    ("03_FRAMES_DOORS" 0 (
      (1920.2595 2346.0) (1887.7863 2324.1221)
    ))
    ; P0901 -- see feature_dimensions_mm.csv
    ("03_FRAMES_DOORS" 0 (
      (2101.4809 2423.1908) (2063.2366 2412.2901) (2025.8473 2399.0534) (1989.4351 2383.542) (1954.1985 2365.8473)
    ))
    ; P0902 -- see feature_dimensions_mm.csv
    ("03_FRAMES_DOORS" 0 (
      (2857.4504 5782.9924) (2817.5725 5775.8015) (2770.5344 5766.6412) (2721.5725 5756.3664) (2671.1603 5744.9924)
      (2619.7557 5732.5038) (2567.8321 5718.8702) (2515.8626 5704.1069) (2464.3206 5688.1985) (2413.6641 5671.145)
      (2364.3664 5652.9313) (2316.8855 5633.5573) (2271.7099 5613.0076) (2229.2977 5591.2672) (2190.1221 5568.3511)
      (2154.6412 5544.229) (2123.3435 5518.916) (2096.6718 5492.3969) (2075.1298 5464.6565) (2059.145 5435.6794)
      (2049.2214 5405.4809) (2045.8015 5374.0458) (2045.8015 4473.2824)
    ))
    ; P0903 -- see feature_dimensions_mm.csv
    ("03_FRAMES_DOORS" 0 (
      (2045.8015 4412.2137) (2045.8015 3832.0611) (2152.6718 3832.0611)
    ))
    ; P0904 -- see feature_dimensions_mm.csv
    ("03_FRAMES_DOORS" 0 (
      (2150.1985 2433.2366) (2140.3969 2431.7252)
    ))
    ; P0905 -- see feature_dimensions_mm.csv
    ("03_FRAMES_DOORS" 0 (
      (2885.1298 5679.3893) (2875.4046 5677.6183) (2835.8779 5669.8473) (2794.2443 5661.0076) (2750.9008 5651.1145)
      (2706.2595 5640.1374) (2660.7634 5628.0916) (2614.8092 5614.9466) (2568.7939 5600.7176) (2523.1603 5585.374)
      (2478.3206 5568.9313) (2434.6718 5551.374) (2392.6565 5532.687) (2352.6565 5512.8702) (2315.1145 5491.9084)
      (2280.4275 5469.8015) (2249.0229 5446.5496) (2221.313 5422.1374) (2197.7099 5396.5649) (2178.626 5369.8168)
      (2164.4885 5341.8779) (2155.6947 5312.7634) (2152.6718 5282.4427) (2152.6718 4473.2824)
    ))
    ; P0906 -- see feature_dimensions_mm.csv
    ("03_FRAMES_DOORS" 0 (
      (2152.6718 4412.2137) (2152.6718 3832.0611)
    ))
    ; P0907 -- see feature_dimensions_mm.csv
    ("03_FRAMES_DOORS" 0 (
      (2152.6718 3832.0611) (2229.0076 3832.0611) (2259.542 3832.0611)
    ))
    ; P0908 -- see feature_dimensions_mm.csv
    ("03_FRAMES_DOORS" 0 (
      (2183.2061 8946.5649) (2183.2061 9236.6412)
    ))
    ; P0909 -- see feature_dimensions_mm.csv
    ("03_FRAMES_DOORS" 0 (
      (2311.1298 5321.2519) (2298.7481 5307.542) (2282.1374 5283.771) (2269.8168 5258.9466) (2262.1679 5233.0534)
      (2259.542 5206.1069) (2259.542 4473.2824)
    ))
    ; P0910 -- see feature_dimensions_mm.csv
    ("03_FRAMES_DOORS" 0 (
      (2259.542 4412.2137) (2259.542 3832.0611)
    ))
    ; P0911 -- see feature_dimensions_mm.csv
    ("03_FRAMES_DOORS" 0 (
      (2259.542 3832.0611) (2938.9313 3832.0611)
    ))
    ; P0912 -- see feature_dimensions_mm.csv
    ("03_FRAMES_DOORS" 0 (
      (2353.0687 5359.2824) (2343.4046 5351.9847) (2319.2824 5330.2901)
    ))
    ; P0913 -- see feature_dimensions_mm.csv
    ("03_FRAMES_DOORS" 0 (
      (2529.6489 2383.542) (2493.2366 2399.0534) (2455.8473 2412.2901) (2417.6031 2423.1908) (2378.687 2431.7252)
      (2368.8855 2433.2366)
    ))
    ; P0914 -- see feature_dimensions_mm.csv
    ("03_FRAMES_DOORS" 0 (
      (2400.9313 5392.3053) (2380.0 5378.687) (2370.7481 5372.6565)
    ))
    ; P0915 -- see feature_dimensions_mm.csv
    ("03_FRAMES_DOORS" 0 (
      (2381.6794 9160.3053) (2381.6794 9083.9695) (2381.6794 8992.3664)
    ))
    ; P0916 -- see feature_dimensions_mm.csv
    ("03_FRAMES_DOORS" 0 (
      (2582.0153 5475.3893) (2566.0305 5469.4046) (2542.9771 5460.7634) (2504.9924 5445.145) (2504.5649 5444.9618)
      (2468.4122 5428.5344) (2456.5649 5422.5496) (2433.6031 5410.9313) (2422.4427 5404.5649)
    ))
    ; P0917 -- see feature_dimensions_mm.csv
    ("03_FRAMES_DOORS" 0 (
      (2505.5115 4473.2824) (2561.3282 4473.2824) (2582.1985 4473.2824) (2608.6412 4473.2824) (2629.5115 4473.2824)
      (2685.3282 4473.2824) (2707.9542 4473.2824) (2741.2672 4473.2824) (2938.9313 4473.2824)
    ))
    ; P0918 -- see feature_dimensions_mm.csv
    ("03_FRAMES_DOORS" 0 (
      (2598.8244 2346.0) (2564.8855 2365.8473)
    ))
    ; P0919 -- see feature_dimensions_mm.csv
    ("03_FRAMES_DOORS" 0 (
      (2653.2977 5498.9924) (2621.7252 5489.0229) (2616.9618 5487.374)
    ))
    ; P0920 -- see feature_dimensions_mm.csv
    ("03_FRAMES_DOORS" 0 (
      (2700.855 5513.084) (2661.771 5501.6641)
    ))
    ; P0921 -- see feature_dimensions_mm.csv
    ("03_FRAMES_DOORS" 0 (
      (2767.313 2187.6183) (2744.0305 2218.1527) (2718.687 2247.1908) (2691.3588 2274.6107) (2662.1985 2300.2901)
    ))
    ; P0922 -- see feature_dimensions_mm.csv
    ("03_FRAMES_DOORS" 0 (
      (2854.9618 8946.5649) (2671.7557 8946.5649) (2671.7557 9236.6412)
    ))
    ; P0923 -- see feature_dimensions_mm.csv
    ("03_FRAMES_DOORS" 0 (
      (3212.8244 5524.0611) (3178.0916 5532.7786) (3173.9847 5533.8168) (3136.2595 5542.6107) (3100.0153 5550.4733)
      (3065.6183 5557.374) (3033.4198 5563.3435) (3003.8015 5568.3969) (2977.0992 5572.5191) (2950.3969 5568.3969)
      (2920.7786 5563.3435) (2888.5802 5557.374) (2854.1832 5550.4733) (2817.9389 5542.6107) (2780.2137 5533.8168)
      (2776.1069 5532.7786) (2741.374 5524.0611)
    ))
    ; P0924 -- see feature_dimensions_mm.csv
    ("03_FRAMES_DOORS" 0 (
      (2748.0916 656.4885) (2809.1603 656.4885)
    ))
    ; P0925 -- see feature_dimensions_mm.csv
    ("03_FRAMES_DOORS" 0 (
      (2823.7405 2088.3817) (2807.2519 2122.5954) (2788.4122 2155.7252)
    ))
    ; P0926 -- see feature_dimensions_mm.csv
    ("03_FRAMES_DOORS" 0 (
      (2809.1603 656.4885) (2824.4275 656.4885) (2824.4275 1862.5954) (2870.229 1862.5954) (2870.229 1868.7023)
      (2868.916 1906.2443) (2865.0076 1943.6336)
    ))
    ; P0927 -- see feature_dimensions_mm.csv
    ("03_FRAMES_DOORS" 0 (
      (2854.7481 1995.8321) (2778.626 2061.0687) (2834.6718 2061.0687)
    ))
    ; P0928 -- see feature_dimensions_mm.csv
    ("03_FRAMES_DOORS" 0 (
      (2858.4885 1980.687) (2857.4962 1984.7328)
    ))
    ; P0929 -- see feature_dimensions_mm.csv
    ("03_FRAMES_DOORS" 0 (
      (2879.3893 5679.3893) (2885.1298 5679.3893)
    ))
    ; P0930 -- see feature_dimensions_mm.csv
    ("03_FRAMES_DOORS" 0 (
      (2885.1298 5679.3893) (3069.0687 5679.3893)
    ))
    ; P0931 -- see feature_dimensions_mm.csv
    ("03_FRAMES_DOORS" 0 (
      (2938.9313 4473.2824) (3015.2672 4473.2824)
    ))
    ; P0932 -- see feature_dimensions_mm.csv
    ("03_FRAMES_DOORS" 0 (
      (3015.2672 4473.2824) (3015.2672 5557.2519) (2938.9313 5557.2519) (2938.9313 4473.2824)
    ))
    ; P0933 -- see feature_dimensions_mm.csv
    ("03_FRAMES_DOORS" 0 (
      (2938.9313 4412.2137) (2938.9313 3832.0611)
    ))
    ; P0934 -- see feature_dimensions_mm.csv
    ("03_FRAMES_DOORS" 0 (
      (2938.9313 3832.0611) (2961.8321 3832.0611)
    ))
    ; P0935 -- see feature_dimensions_mm.csv
    ("03_FRAMES_DOORS" 0 (
      (3015.2672 4473.2824) (3212.9313 4473.2824) (3246.2443 4473.2824) (3268.8702 4473.2824) (3324.687 4473.2824)
      (3345.5573 4473.2824) (3372.0 4473.2824) (3392.8702 4473.2824) (3448.687 4473.2824)
    ))
    ; P0936 -- see feature_dimensions_mm.csv
    ("03_FRAMES_DOORS" 0 (
      (3694.6565 4412.2137) (3510.3359 4412.2137) (3482.0305 4412.2137) (3372.9313 4412.2137) (3344.626 4412.2137)
      (3235.5267 4412.2137) (3207.2214 4412.2137) (3015.2672 4412.2137)
    ))
    ; P0937 -- see feature_dimensions_mm.csv
    ("03_FRAMES_DOORS" 0 (
      (3015.2672 3832.0611) (3015.2672 4412.2137)
    ))
    ; P0938 -- see feature_dimensions_mm.csv
    ("03_FRAMES_DOORS" 0 (
      (3015.2672 4412.2137) (2992.3664 4412.2137) (2992.3664 3832.0611) (3015.2672 3832.0611)
    ))
    ; P0939 -- see feature_dimensions_mm.csv
    ("03_FRAMES_DOORS" 0 (
      (3015.2672 3832.0611) (3694.6565 3832.0611)
    ))
    ; P0940 -- see feature_dimensions_mm.csv
    ("03_FRAMES_DOORS" 0 (
      (3069.0687 5679.3893) (3074.8092 5679.3893)
    ))
    ; P0941 -- see feature_dimensions_mm.csv
    ("03_FRAMES_DOORS" 0 (
      (3801.5267 4473.2824) (3801.5267 5282.4427) (3798.5038 5312.7634) (3789.7099 5341.8779) (3775.5725 5369.8168)
      (3756.4885 5396.5649) (3732.8855 5422.1374) (3705.1756 5446.5496) (3673.771 5469.8015) (3639.084 5491.9084)
      (3601.542 5512.8702) (3561.542 5532.687) (3519.5267 5551.374) (3475.8779 5568.9313) (3431.0382 5585.374)
      (3385.4046 5600.7176) (3339.3893 5614.9466) (3293.4351 5628.0916) (3247.9389 5640.1374) (3203.2977 5651.1145)
      (3159.9542 5661.0076) (3118.3206 5669.8473) (3078.7939 5677.6183) (3069.0687 5679.3893)
    ))
    ; P0942 -- see feature_dimensions_mm.csv
    ("03_FRAMES_DOORS" 0 (
      (3801.5267 4473.2824) (3908.3969 4473.2824) (3908.3969 5374.0458) (3904.9771 5405.4809) (3895.0534 5435.6794)
      (3879.0687 5464.6565) (3857.5267 5492.3969) (3830.855 5518.916) (3799.5573 5544.229) (3764.0763 5568.3511)
      (3724.9008 5591.2672) (3682.4885 5613.0076) (3637.313 5633.5573) (3589.8321 5652.9313) (3540.5344 5671.145)
      (3489.8779 5688.1985) (3438.3359 5704.1069) (3386.3664 5718.8702) (3334.4427 5732.5038) (3283.0382 5744.9924)
      (3232.626 5756.3664) (3183.6641 5766.6412) (3136.626 5775.8015) (3096.7481 5782.9924)
    ))
    ; P0943 -- see feature_dimensions_mm.csv
    ("03_FRAMES_DOORS" 0 (
      (3358.7786 9236.6412) (3358.7786 8946.5649) (3206.1069 8946.5649)
    ))
    ; P0944 -- see feature_dimensions_mm.csv
    ("03_FRAMES_DOORS" 0 (
      (3299.8473 2284.9924) (3283.7557 2259.542) (3269.3893 2233.1145) (3256.8244 2205.8015) (3246.0916 2177.7557)
      (3237.2366 2149.084) (3230.3206 2119.8931) (3225.3588 2090.3206) (3222.3664 2060.4885) (3221.374 2030.5344)
    ))
    ; P0945 -- see feature_dimensions_mm.csv
    ("03_FRAMES_DOORS" 0 (
      (3252.4275 5513.3435) (3225.6489 5520.5954)
    ))
    ; P0946 -- see feature_dimensions_mm.csv
    ("03_FRAMES_DOORS" 0 (
      (3508.8244 2453.6794) (3481.0687 2441.313) (3454.1985 2427.1908) (3428.3206 2411.3588) (3403.5573 2393.9084)
      (3380.0 2374.8855) (3357.7557 2354.3969) (3336.9313 2332.5191) (3317.6031 2309.3588)
    ))
    ; P0947 -- see feature_dimensions_mm.csv
    ("03_FRAMES_DOORS" 0 (
      (3449.2061 5445.145) (3411.2214 5460.7634) (3388.1679 5469.4046)
    ))
    ; P0948 -- see feature_dimensions_mm.csv
    ("03_FRAMES_DOORS" 0 (
      (3583.4656 5372.6565) (3574.1985 5378.687) (3553.2672 5392.3053)
    ))
    ; P0949 -- see feature_dimensions_mm.csv
    ("03_FRAMES_DOORS" 0 (
      (3574.3053 2474.7328) (3566.5038 2472.9466)
    ))
    ; P0950 -- see feature_dimensions_mm.csv
    ("03_FRAMES_DOORS" 0 (
      (3594.1985 2381.6794) (3593.5573 2384.7023) (3586.2595 2382.9008) (3561.8779 2375.0687) (3538.0458 2365.5725)
      (3514.8397 2354.4427) (3492.3664 2341.7252) (3470.7328 2327.4809) (3450.0305 2311.771) (3430.3359 2294.6565)
      (3411.7405 2276.2137) (3394.3206 2256.5191) (3378.1527 2235.6794) (3363.3282 2213.7405) (3349.8626 2190.8397)
      (3337.8626 2167.0534) (3327.3435 2142.4733) (3318.3664 2117.2366) (3310.9771 2091.4198) (3305.1908 2065.145)
      (3301.0382 2038.5344) (3298.5496 2011.6947) (3297.7099 1984.7328) (3297.7099 503.8168) (4076.3359 503.8168)
      (4076.3359 1984.7328) (4075.4962 2011.6947) (4073.0076 2038.5344) (4068.855 2065.145) (4063.0687 2091.4198)
      (4055.6794 2117.2366) (4046.7023 2142.4733) (4036.1832 2167.0534) (4024.1832 2190.8397) (4010.7176 2213.7405)
      (3995.8931 2235.6794) (3979.7252 2256.5191) (3962.3053 2276.2137) (3943.7099 2294.6565) (3924.0153 2311.771)
      (3903.313 2327.4809) (3881.6794 2341.7252) (3859.2061 2354.4427) (3836.0 2365.5725) (3812.1679 2375.0687)
      (3787.7863 2382.9008) (3780.4885 2384.7023) (3779.8473 2381.6794)
    ))
    ; P0951 -- see feature_dimensions_mm.csv
    ("03_FRAMES_DOORS" 0 (
      (3634.916 5330.2901) (3610.7939 5351.9847) (3601.1298 5359.2824)
    ))
    ; P0952 -- see feature_dimensions_mm.csv
    ("03_FRAMES_DOORS" 0 (
      (3801.5267 4473.2824) (3694.6565 4473.2824) (3694.6565 5206.1069) (3692.0305 5233.0534) (3684.3817 5258.9466)
      (3672.0611 5283.771) (3655.4504 5307.542) (3643.0687 5321.2519)
    ))
    ; P0953 -- see feature_dimensions_mm.csv
    ("03_FRAMES_DOORS" 0 (
      (3648.855 9312.9771) (3847.3282 9312.9771) (3847.3282 9236.6412)
    ))
    ; P0954 -- see feature_dimensions_mm.csv
    ("03_FRAMES_DOORS" 0 (
      (3847.3282 9160.3053) (3847.3282 9083.9695) (3847.3282 8992.3664) (3847.3282 8946.5649) (3648.855 8946.5649)
      (3648.855 8992.3664)
    ))
    ; P0955 -- see feature_dimensions_mm.csv
    ("03_FRAMES_DOORS" 0 (
      (3694.6565 3832.0611) (3725.1908 3832.0611) (3755.7252 3832.0611) (3801.5267 3832.0611) (3801.5267 4412.2137)
      (3755.7252 4412.2137) (3725.1908 4412.2137) (3694.6565 4412.2137)
    ))
    ; P0956 -- see feature_dimensions_mm.csv
    ("03_FRAMES_DOORS" 0 (
      (3694.6565 3832.0611) (3694.6565 4412.2137)
    ))
    ; P0957 -- see feature_dimensions_mm.csv
    ("03_FRAMES_DOORS" 0 (
      (3908.3969 3832.0611) (3908.3969 4412.2137)
    ))
    ; P0958 -- see feature_dimensions_mm.csv
    ("03_FRAMES_DOORS" 0 (
      (4117.2214 2205.8015) (4104.6565 2233.1145)
    ))
    ; P0959 -- see feature_dimensions_mm.csv
    ("03_FRAMES_DOORS" 0 (
      (5297.7099 961.8321) (5246.8244 1053.4351) (5221.374 1099.2366) (6122.1374 1099.2366) (6096.687 1053.4351)
      (6045.8015 961.8321)
    ))
    ; P0960 -- see feature_dimensions_mm.csv
    ("03_FRAMES_DOORS" 0 (
      (6335.8779 961.8321) (6284.9924 1053.4351) (6259.542 1099.2366) (7480.916 1099.2366) (7455.4656 1053.4351)
      (7404.5802 961.8321)
    ))
    ; P0961 -- see feature_dimensions_mm.csv
    ("03_FRAMES_DOORS" 0 (
      (7618.3206 1587.7863) (7618.3206 2213.7405)
    ))
    ; P0962 -- see feature_dimensions_mm.csv
    ("03_FRAMES_DOORS" 0 (
      (7664.7634 5554.5954) (7678.6565 5580.1527)
    ))
    ; P0963 -- see feature_dimensions_mm.csv
    ("03_FRAMES_DOORS" 0 (
      (7711.3893 5628.3053) (7730.0916 5650.7023)
    ))
    ; P0964 -- see feature_dimensions_mm.csv
    ("03_FRAMES_DOORS" 0 (
      (7750.229 5671.8473) (7771.7405 5691.6489)
    ))
    ; P0965 -- see feature_dimensions_mm.csv
    ("03_FRAMES_DOORS" 0 (
      (7952.1374 5786.4427) (7980.8397 5793.0229)
    ))
    ; P0966 -- see feature_dimensions_mm.csv
    ("03_FRAMES_DOORS" 0 (
      (8098.1527 5800.5802) (8127.4962 5797.7405)
    ))
    ; P0967 -- see feature_dimensions_mm.csv
    ("03_FRAMES_DOORS" 0 (
      (8426.0153 5628.3053) (8443.1756 5604.7634)
    ))
    ; P0968 -- see feature_dimensions_mm.csv
    ("03_FRAMES_DOORS" 1 (
      (8473.2824 1099.2366) (7618.3206 1099.2366) (7643.771 1053.4351) (7694.6565 961.8321) (8442.7481 961.8321)
      (8473.2824 1016.7939) (8473.2824 1053.4351)
    ))
    ; P0969 -- see feature_dimensions_mm.csv
    ("03_FRAMES_DOORS" 0 (
      (8473.2824 1099.2366) (8473.2824 3618.3206) (8519.084 3618.3206)
    ))
    ; P0970 -- see feature_dimensions_mm.csv
    ("03_FRAMES_DOORS" 0 (
      (8518.1221 5387.7405) (8519.084 5358.7786)
    ))
    ; P0971 -- see feature_dimensions_mm.csv
    ("03_FRAMES_DOORS" 0 (
      (8748.0916 320.6107) (10229.0076 320.6107) (10244.2748 320.6107)
    ))
    ; P0972 -- see feature_dimensions_mm.csv
    ("03_FRAMES_DOORS" 0 (
      (10244.2748 320.6107) (10335.8779 320.6107) (10335.8779 3404.5802) (8656.4885 3404.5802) (8656.4885 320.6107)
      (8702.2901 320.6107) (8748.0916 320.6107)
    ))
    ; P0973 -- see feature_dimensions_mm.csv
    ("03_FRAMES_DOORS" 0 (
      (10244.2748 320.6107) (10244.2748 3312.9771) (8748.0916 3312.9771) (8748.0916 396.9466) (8748.0916 320.6107)
    ))
    ; P0974 -- see feature_dimensions_mm.csv
    ("03_FRAMES_DOORS" 0 (
      (8885.4962 4412.2137) (8793.8931 4412.2137)
    ))
    ; P0975 -- see feature_dimensions_mm.csv
    ("03_FRAMES_DOORS" 0 (
      (8885.4962 4473.2824) (8793.8931 4473.2824) (8793.8931 5358.7786) (8796.4427 5382.3511) (8803.8473 5405.0076)
    ))
    ; P0976 -- see feature_dimensions_mm.csv
    ("03_FRAMES_DOORS" 0 (
      (8815.771 5426.7328) (8831.8473 5447.542) (8851.7252 5467.4351) (8875.084 5486.4275) (8901.542 5504.5038)
      (8930.7634 5521.6947) (8962.3969 5538.0) (8996.1069 5553.4046) (9031.5115 5567.9389) (9068.2901 5581.6031)
      (9106.0611 5594.3969) (9144.5191 5606.3206) (9183.2824 5617.3893) (9222.0 5627.6183) (9260.3511 5636.9924)
      (9297.9542 5645.5267) (9334.4733 5653.2214)
    ))
    ; P0977 -- see feature_dimensions_mm.csv
    ("03_FRAMES_DOORS" 0 (
      (8885.4962 4473.2824) (8946.5649 4473.2824)
    ))
    ; P0978 -- see feature_dimensions_mm.csv
    ("03_FRAMES_DOORS" 0 (
      (10091.6031 4473.2824) (10091.6031 5267.1756) (10089.3893 5289.6336) (10082.9618 5311.2061) (10072.6107 5331.8931)
      (10058.6565 5351.7099) (10041.3893 5370.6565) (10021.1145 5388.7328) (9998.1527 5405.9695) (9972.7786 5422.3359)
      (9945.313 5437.8626) (9916.0611 5452.5344) (9885.3282 5466.3817) (9853.4046 5479.3893) (9820.5954 5491.5725)
      (9787.2214 5502.9313) (9753.5573 5513.4809) (9719.9389 5523.2061) (9686.6565 5532.1374) (9654.0153 5540.2595)
      (9622.3053 5547.6031) (9591.8473 5554.1374) (9562.9466 5559.8931) (9535.8931 5564.8855) (9510.9924 5569.084)
      (9488.5496 5572.5191) (9466.1069 5569.084) (9441.2061 5564.8855) (9414.1527 5559.8931) (9385.2519 5554.1374)
      (9354.7939 5547.6031) (9323.084 5540.2595) (9290.4427 5532.1374) (9257.1603 5523.2061) (9223.542 5513.4809)
      (9189.8779 5502.9313) (9156.5038 5491.5725) (9123.7099 5479.3893) (9091.771 5466.3817) (9061.0382 5452.5344)
      (9031.7863 5437.8626) (9004.3206 5422.3359) (8978.9466 5405.9695) (8955.9847 5388.7328) (8935.7099 5370.6565)
      (8918.4427 5351.7099) (8904.4885 5331.8931) (8894.1374 5311.2061) (8887.7099 5289.6336) (8885.4962 5267.1756)
      (8885.4962 4473.2824)
    ))
    ; P0979 -- see feature_dimensions_mm.csv
    ("03_FRAMES_DOORS" 0 (
      (8946.5649 4412.2137) (8885.4962 4412.2137)
    ))
    ; P0980 -- see feature_dimensions_mm.csv
    ("03_FRAMES_DOORS" 0 (
      (8885.4962 4412.2137) (8885.4962 3832.0611)
    ))
    ; P0981 -- see feature_dimensions_mm.csv
    ("03_FRAMES_DOORS" 0 (
      (8946.5649 4473.2824) (9465.6489 4473.2824)
    ))
    ; P0982 -- see feature_dimensions_mm.csv
    ("03_FRAMES_DOORS" 0 (
      (8988.626 5305.8473) (8976.1679 5290.6412) (8971.3893 5283.084) (8970.4733 5281.6489) (8963.6336 5270.8244)
      (8954.3359 5250.1374) (8948.5496 5228.5649) (8946.5649 5206.1069) (8946.5649 4473.2824)
    ))
    ; P0983 -- see feature_dimensions_mm.csv
    ("03_FRAMES_DOORS" 0 (
      (9238.1679 4412.2137) (9158.7786 4412.2137) (9100.7634 4412.2137) (9021.374 4412.2137) (8946.5649 4412.2137)
    ))
    ; P0984 -- see feature_dimensions_mm.csv
    ("03_FRAMES_DOORS" 0 (
      (8946.5649 4412.2137) (8946.5649 3832.0611)
    ))
    ; P0985 -- see feature_dimensions_mm.csv
    ("03_FRAMES_DOORS" 0 (
      (9031.4656 5345.5573) (9030.5496 5344.9008) (9009.9084 5327.6641) (9002.4275 5320.2443) (8991.6947 5309.5878)
    ))
    ; P0986 -- see feature_dimensions_mm.csv
    ("03_FRAMES_DOORS" 0 (
      (9088.0 5382.3511) (9078.0458 5376.7939) (9061.6031 5366.458) (9053.3588 5361.2672)
    ))
    ; P0987 -- see feature_dimensions_mm.csv
    ("03_FRAMES_DOORS" 0 (
      (9190.1374 5430.5038) (9175.4351 5424.4275) (9160.6565 5418.3206) (9131.9542 5405.313) (9126.7786 5402.7176)
      (9104.3359 5391.4656)
    ))
    ; P0988 -- see feature_dimensions_mm.csv
    ("03_FRAMES_DOORS" 0 (
      (9280.5954 5462.1374) (9250.3664 5452.4122) (9243.7405 5450.0916) (9220.1221 5441.8626) (9214.1374 5439.6031)
    ))
    ; P0989 -- see feature_dimensions_mm.csv
    ("03_FRAMES_DOORS" 0 (
      (9298.9771 5467.6336) (9281.374 5462.3817)
    ))
    ; P0990 -- see feature_dimensions_mm.csv
    ("03_FRAMES_DOORS" 0 (
      (9450.3817 4412.2137) (9375.5725 4412.2137) (9296.1832 4412.2137)
    ))
    ; P0991 -- see feature_dimensions_mm.csv
    ("03_FRAMES_DOORS" 0 (
      (9666.5954 5471.0687) (9640.3206 5478.3511) (9637.2519 5479.1908) (9608.7634 5486.5344) (9581.3893 5493.0687)
      (9555.4046 5498.8244) (9531.0992 5503.8168) (9508.7176 5508.0153) (9488.5496 5511.4504) (9468.3817 5508.0153)
      (9446.0 5503.8168) (9421.6947 5498.8244) (9395.7099 5493.0687) (9368.3359 5486.5344) (9339.8473 5479.1908)
      (9336.7786 5478.3511) (9310.5038 5471.0687)
    ))
    ; P0992 -- see feature_dimensions_mm.csv
    ("03_FRAMES_DOORS" 0 (
      (9383.9389 2509.2519) (9383.0076 2509.1145) (9346.0305 2501.3893) (9309.6947 2491.542) (9274.1679 2479.5725)
      (9239.5878 2465.5573) (9206.1069 2449.542) (9173.8626 2431.6031) (9143.0076 2411.8168) (9113.6641 2390.2748)
      (9085.9542 2367.0534) (9060.0 2342.2595) (9035.9237 2316.0) (9013.8015 2288.3817) (8993.7557 2259.542)
      (8975.8626 2229.5878) (8960.1985 2198.6412) (8946.8244 2166.855) (8935.8015 2134.3511) (8927.1756 2101.2672)
      (8920.9924 2067.7557) (8917.2672 2033.9542) (8916.0305 2000.0) (8916.0305 396.9466) (8916.0305 381.6794)
      (10076.3359 381.6794) (10076.3359 396.9466) (10076.3359 2000.0) (10075.0992 2033.9542) (10071.374 2067.7557)
      (10065.1908 2101.2672) (10056.5649 2134.3511) (10045.542 2166.855) (10032.1679 2198.6412) (10016.5038 2229.5878)
      (9998.6107 2259.542) (9978.5649 2288.3817) (9956.4427 2316.0) (9932.3664 2342.2595) (9906.4122 2367.0534)
      (9878.7023 2390.2748) (9849.3588 2411.8168) (9818.5038 2431.6031) (9786.2595 2449.542) (9752.7786 2465.5573)
      (9718.1985 2479.5725) (9682.6718 2491.542) (9646.3359 2501.3893) (9609.3588 2509.1145) (9608.4427 2509.2519)
      (9584.1221 2381.6794)
    ))
    ; P0993 -- see feature_dimensions_mm.csv
    ("03_FRAMES_DOORS" 0 (
      (9400.4733 3832.0611) (9427.0076 3832.0611)
    ))
    ; P0994 -- see feature_dimensions_mm.csv
    ("03_FRAMES_DOORS" 0 (
      (9434.0153 5671.374) (9462.7023 5675.7863) (9488.5496 5679.3893)
    ))
    ; P0995 -- see feature_dimensions_mm.csv
    ("03_FRAMES_DOORS" 0 (
      (9465.6489 4473.2824) (9511.4504 4473.2824)
    ))
    ; P0996 -- see feature_dimensions_mm.csv
    ("03_FRAMES_DOORS" 0 (
      (9511.4504 4473.2824) (9511.4504 5496.1832) (9465.6489 5496.1832) (9465.6489 4473.2824)
    ))
    ; P0997 -- see feature_dimensions_mm.csv
    ("03_FRAMES_DOORS" 0 (
      (9503.8168 4412.2137) (9503.8168 3832.0611)
    ))
    ; P0998 -- see feature_dimensions_mm.csv
    ("03_FRAMES_DOORS" 0 (
      (9511.4504 4473.2824) (10030.5344 4473.2824)
    ))
    ; P0999 -- see feature_dimensions_mm.csv
    ("03_FRAMES_DOORS" 0 (
      (9511.4504 3832.0611) (9511.4504 4412.2137)
    ))
    ; P1000 -- see feature_dimensions_mm.csv
    ("03_FRAMES_DOORS" 0 (
      (9762.9618 5439.6031) (9756.9771 5441.8626) (9733.3588 5450.0916)
    ))
    ; P1001 -- see feature_dimensions_mm.csv
    ("03_FRAMES_DOORS" 0 (
      (9872.7634 5391.4656) (9850.3206 5402.7176) (9845.145 5405.313) (9816.458 5418.3206) (9801.6641 5424.4275)
      (9786.9618 5430.5038)
    ))
    ; P1002 -- see feature_dimensions_mm.csv
    ("03_FRAMES_DOORS" 0 (
      (9923.7405 5361.2672) (9915.4962 5366.458) (9899.0534 5376.7939) (9889.0992 5382.3511)
    ))
    ; P1003 -- see feature_dimensions_mm.csv
    ("03_FRAMES_DOORS" 0 (
      (9988.1985 5306.1832) (9988.1679 5306.229) (9985.4046 5309.5878) (9974.6718 5320.2443) (9967.1908 5327.6641)
      (9946.5496 5344.9008) (9945.6336 5345.5573)
    ))
    ; P1004 -- see feature_dimensions_mm.csv
    ("03_FRAMES_DOORS" 0 (
      (9993.8473 5299.2824) (9991.6489 5301.9847) (9990.7023 5303.1298) (9988.4733 5305.8473) (9988.2901 5306.0763)
    ))
    ; P1005 -- see feature_dimensions_mm.csv
    ("03_FRAMES_DOORS" 0 (
      (10030.5344 4473.2824) (10030.5344 5206.1069) (10028.5496 5228.5649) (10022.7634 5250.1374) (10013.4656 5270.8244)
      (10006.626 5281.6489) (10005.7099 5283.084) (10000.9313 5290.6412) (9998.2748 5293.8779)
    ))
    ; P1006 -- see feature_dimensions_mm.csv
    ("03_FRAMES_DOORS" 0 (
      (10030.5344 4473.2824) (10091.6031 4473.2824)
    ))
    ; P1007 -- see feature_dimensions_mm.csv
    ("03_FRAMES_DOORS" 0 (
      (10030.5344 3832.0611) (10030.5344 4412.2137)
    ))
    ; P1008 -- see feature_dimensions_mm.csv
    ("03_FRAMES_DOORS" 0 (
      (10091.6031 4473.2824) (10183.2061 4473.2824)
    ))
    ; P1009 -- see feature_dimensions_mm.csv
    ("03_FRAMES_DOORS" 0 (
      (10091.6031 3832.0611) (10091.6031 4412.2137)
    ))
    ; P1010 -- see feature_dimensions_mm.csv
    ("03_FRAMES_DOORS" 0 (
      (10125.374 5467.4351) (10145.2519 5447.542) (10161.3282 5426.7328) (10173.2519 5405.0076) (10180.6565 5382.3511)
      (10183.2061 5358.7786)
    ))
    ; P1011 -- see feature_dimensions_mm.csv
    ("03_FRAMES_DOORS" 0 (
      (10580.1527 1282.4427) (10580.1527 931.2977) (10580.1527 656.4885)
    ))
    ; P1012 -- see feature_dimensions_mm.csv
    ("03_FRAMES_DOORS" 0 (
      (10610.687 1862.5954) (10809.1603 1862.5954) (10854.9618 1862.5954) (10854.9618 656.4885)
    ))
    ; P1013 -- see feature_dimensions_mm.csv
    ("03_FRAMES_DOORS" 0 (
      (10885.4962 2061.0687) (10825.4809 1989.0534) (10819.7252 1965.8321) (10813.8626 1932.4733) (10810.3359 1898.8244)
      (10809.1603 1865.0382)
    ))
    ; P1014 -- see feature_dimensions_mm.csv
    ("03_FRAMES_DOORS" 0 (
      (10829.9084 2155.7252) (10811.0687 2122.5954)
    ))
    ; P1015 -- see feature_dimensions_mm.csv
    ("03_FRAMES_DOORS" 0 (
      (11265.9542 2351.145) (11261.4962 2373.2977) (11251.5573 2371.7557) (11216.5344 2364.0763) (11182.1069 2354.2595)
      (11148.4427 2342.3511) (11115.6947 2328.3969) (11083.9695 2312.458) (11053.4198 2294.6107) (11024.1985 2274.916)
      (10996.3969 2253.4656) (10970.1374 2230.3511) (10945.5573 2205.6794) (10922.7328 2179.542) (10901.7863 2152.0611)
      (10882.7939 2123.3588) (10865.8473 2093.542) (10850.9924 2062.7481) (10850.3206 2061.0687)
    ))
    ; P1016 -- see feature_dimensions_mm.csv
    ("03_FRAMES_DOORS" 0 (
      (11847.3282 656.4885) (11847.3282 1861.374) (11846.2748 1891.4046) (11843.145 1921.313) (11837.9389 1950.9618)
      (11830.687 1980.229) (11821.4046 2008.9924) (11810.1374 2037.1145) (11796.9466 2064.4885) (11781.8779 2090.9924)
      (11764.9924 2116.5191) (11746.3664 2140.9466) (11726.0916 2164.1679) (11704.229 2186.1069) (11680.9008 2206.6412)
      (11656.1832 2225.7099) (11630.1985 2243.2214) (11603.0534 2259.084) (11574.855 2273.2519) (11545.7405 2285.6489)
      (11515.8168 2296.2443) (11485.2214 2304.9618) (11454.0916 2311.7863) (11422.5496 2316.687) (11390.7328 2319.6336)
      (11358.7786 2320.6107) (11326.8244 2319.6336) (11295.0076 2316.687) (11263.4656 2311.7863) (11232.3359 2304.9618)
      (11201.7405 2296.2443) (11171.8168 2285.6489) (11142.7023 2273.2519) (11114.5038 2259.084) (11087.3588 2243.2214)
      (11061.374 2225.7099) (11036.6565 2206.6412) (11013.3282 2186.1069) (10991.4656 2164.1679) (10971.1908 2140.9466)
      (10952.5649 2116.5191) (10935.6794 2090.9924) (10920.6107 2064.4885) (10907.4198 2037.1145) (10896.1527 2008.9924)
      (10886.8702 1980.229) (10879.6183 1950.9618) (10874.4122 1921.313) (10871.2824 1891.4046) (10870.229 1861.374)
      (10870.229 656.4885)
    ))
    ; P1017 -- see feature_dimensions_mm.csv
    ("03_FRAMES_DOORS" 0 (
      (11019.4962 2346.0) (10987.0229 2324.1221)
    ))
    ; P1018 -- see feature_dimensions_mm.csv
    ("03_FRAMES_DOORS" 0 (
      (11160.3053 2961.8321) (11160.3053 2809.1603) (11038.1679 2809.1603) (11038.1679 2961.8321)
    ))
    ; P1019 -- see feature_dimensions_mm.csv
    ("03_FRAMES_DOORS" 0 (
      (11088.6718 2383.542) (11053.4351 2365.8473)
    ))
    ; P1020 -- see feature_dimensions_mm.csv
    ("03_FRAMES_DOORS" 0 (
      (11129.771 4412.2137) (11129.771 3832.0611)
    ))
    ; P1021 -- see feature_dimensions_mm.csv
    ("03_FRAMES_DOORS" 0 (
      (11236.6412 4473.2824) (11343.5115 4473.2824)
    ))
    ; P1022 -- see feature_dimensions_mm.csv
    ("03_FRAMES_DOORS" 0 (
      (11941.4198 5782.9924) (11901.542 5775.8015) (11854.5038 5766.6412) (11805.542 5756.3664) (11755.1298 5744.9924)
      (11703.7252 5732.5038) (11651.8015 5718.8702) (11599.8321 5704.1069) (11548.2901 5688.1985) (11497.6336 5671.145)
      (11448.3359 5652.9313) (11400.855 5633.5573) (11355.6794 5613.0076) (11313.2672 5591.2672) (11274.0916 5568.3511)
      (11238.6107 5544.229) (11207.313 5518.916) (11180.6412 5492.3969) (11159.0992 5464.6565) (11143.1145 5435.6794)
      (11133.1908 5405.4809) (11129.771 5374.0458) (11129.771 4473.2824) (11236.6412 4473.2824)
    ))
    ; P1023 -- see feature_dimensions_mm.csv
    ("03_FRAMES_DOORS" 0 (
      (11969.0992 5679.3893) (11959.374 5677.6183) (11919.8473 5669.8473) (11878.2137 5661.0076) (11834.8702 5651.1145)
      (11790.229 5640.1374) (11744.7328 5628.0916) (11698.7786 5614.9466) (11652.7634 5600.7176) (11607.1298 5585.374)
      (11562.2901 5568.9313) (11518.6412 5551.374) (11476.626 5532.687) (11436.626 5512.8702) (11399.084 5491.9084)
      (11364.3969 5469.8015) (11332.9924 5446.5496) (11305.2824 5422.1374) (11281.6794 5396.5649) (11262.5954 5369.8168)
      (11248.458 5341.8779) (11239.6641 5312.7634) (11236.6412 5282.4427) (11236.6412 4473.2824)
    ))
    ; P1024 -- see feature_dimensions_mm.csv
    ("03_FRAMES_DOORS" 0 (
      (11236.6412 4412.2137) (11236.6412 3832.0611)
    ))
    ; P1025 -- see feature_dimensions_mm.csv
    ("03_FRAMES_DOORS" 0 (
      (11435.1145 2961.8321) (11435.1145 2809.1603) (11312.9771 2809.1603) (11312.9771 2961.8321)
    ))
    ; P1026 -- see feature_dimensions_mm.csv
    ("03_FRAMES_DOORS" 0 (
      (11343.5115 4473.2824) (11533.542 4473.2824) (11566.855 4473.2824) (11589.4809 4473.2824) (11645.2977 4473.2824)
      (11666.1679 4473.2824) (11692.6107 4473.2824) (11713.4809 4473.2824) (11769.2977 4473.2824) (11791.9237 4473.2824)
      (11825.2366 4473.2824) (12022.9008 4473.2824)
    ))
    ; P1027 -- see feature_dimensions_mm.csv
    ("03_FRAMES_DOORS" 0 (
      (11395.0992 5321.2519) (11382.7176 5307.542) (11366.1069 5283.771) (11353.7863 5258.9466) (11346.1374 5233.0534)
      (11343.5115 5206.1069) (11343.5115 4473.2824)
    ))
    ; P1028 -- see feature_dimensions_mm.csv
    ("03_FRAMES_DOORS" 0 (
      (11343.5115 4412.2137) (11343.5115 3832.0611)
    ))
    ; P1029 -- see feature_dimensions_mm.csv
    ("03_FRAMES_DOORS" 0 (
      (11437.0382 5359.2824) (11427.374 5351.9847) (11403.2519 5330.2901)
    ))
    ; P1030 -- see feature_dimensions_mm.csv
    ("03_FRAMES_DOORS" 0 (
      (11867.2366 2061.0687) (11866.5649 2062.7481) (11851.7099 2093.542) (11834.7634 2123.3588) (11815.771 2152.0611)
      (11794.8244 2179.542) (11772.0 2205.6794) (11747.4198 2230.3511) (11721.1603 2253.4656) (11693.3588 2274.916)
      (11664.1374 2294.6107) (11633.5878 2312.458) (11601.8626 2328.3969) (11569.1145 2342.3511) (11535.4504 2354.2595)
      (11501.0229 2364.0763) (11466.0 2371.7557) (11456.0611 2373.2977) (11451.6031 2351.145)
    ))
    ; P1031 -- see feature_dimensions_mm.csv
    ("03_FRAMES_DOORS" 0 (
      (11484.9008 5392.3053) (11463.9695 5378.687) (11454.7176 5372.6565)
    ))
    ; P1032 -- see feature_dimensions_mm.csv
    ("03_FRAMES_DOORS" 0 (
      (11516.8397 2423.1908) (11477.9237 2431.7252)
    ))
    ; P1033 -- see feature_dimensions_mm.csv
    ("03_FRAMES_DOORS" 0 (
      (11665.9847 5475.3893) (11650.0 5469.4046) (11626.9466 5460.7634) (11588.9618 5445.145) (11588.5344 5444.9618)
      (11552.3817 5428.5344) (11540.5344 5422.5496) (11517.5725 5410.9313) (11506.4122 5404.5649)
    ))
    ; P1034 -- see feature_dimensions_mm.csv
    ("03_FRAMES_DOORS" 0 (
      (11725.1908 3099.2366) (11725.1908 2961.8321) (11725.1908 2809.1603) (11603.0534 2809.1603) (11603.0534 2961.8321)
    ))
    ; P1035 -- see feature_dimensions_mm.csv
    ("03_FRAMES_DOORS" 0 (
      (11698.0611 2346.0) (11664.1221 2365.8473)
    ))
    ; P1036 -- see feature_dimensions_mm.csv
    ("03_FRAMES_DOORS" 0 (
      (11737.2672 5498.9924) (11705.6947 5489.0229) (11700.9313 5487.374)
    ))
    ; P1037 -- see feature_dimensions_mm.csv
    ("03_FRAMES_DOORS" 0 (
      (12376.3969 5501.6641) (12337.313 5513.084) (12336.3969 5513.3435) (12309.6183 5520.5954) (12296.7939 5524.0611)
      (12262.0611 5532.7786) (12257.9542 5533.8168) (12220.229 5542.6107) (12183.9847 5550.4733) (12149.5878 5557.374)
      (12117.3893 5563.3435) (12087.771 5568.3969) (12061.0687 5572.5191) (12034.3664 5568.3969) (12004.7481 5563.3435)
      (11972.5496 5557.374) (11938.1527 5550.4733) (11901.9084 5542.6107) (11864.1832 5533.8168) (11860.0763 5532.7786)
      (11825.3435 5524.0611) (11812.5191 5520.5954) (11785.7405 5513.3435) (11784.8244 5513.084) (11745.7405 5501.6641)
    ))
    ; P1038 -- see feature_dimensions_mm.csv
    ("03_FRAMES_DOORS" 0 (
      (11867.2366 2061.0687) (11933.9084 2061.0687)
    ))
    ; P1039 -- see feature_dimensions_mm.csv
    ("03_FRAMES_DOORS" 0 (
      (11877.6336 2035.0992) (11847.3282 2061.0687) (11867.2366 2061.0687)
    ))
    ; P1040 -- see feature_dimensions_mm.csv
    ("03_FRAMES_DOORS" 0 (
      (11963.5267 1947.6947) (11954.1985 1969.4656) (11877.6336 2035.0992)
    ))
    ; P1041 -- see feature_dimensions_mm.csv
    ("03_FRAMES_DOORS" 0 (
      (11908.3969 656.4885) (11908.3969 1865.0382) (11907.2214 1898.8244) (11903.6947 1932.4733) (11897.8321 1965.8321)
      (11889.6641 1998.7481) (11879.2214 2031.1145) (11877.6336 2035.0992)
    ))
    ; P1042 -- see feature_dimensions_mm.csv
    ("03_FRAMES_DOORS" 0 (
      (11963.3588 5679.3893) (11969.0992 5679.3893)
    ))
    ; P1043 -- see feature_dimensions_mm.csv
    ("03_FRAMES_DOORS" 0 (
      (11969.4656 1868.7023) (11968.1527 1906.2443)
    ))
    ; P1044 -- see feature_dimensions_mm.csv
    ("03_FRAMES_DOORS" 0 (
      (11969.0992 5679.3893) (12153.0382 5679.3893)
    ))
    ; P1045 -- see feature_dimensions_mm.csv
    ("03_FRAMES_DOORS" 0 (
      (11969.4656 656.4885) (11923.6641 656.4885) (11923.6641 1862.5954) (11969.4656 1862.5954)
    ))
    ; P1046 -- see feature_dimensions_mm.csv
    ("03_FRAMES_DOORS" 1 (
      (12022.9008 4473.2824) (12099.2366 4473.2824) (12099.2366 5557.2519) (12022.9008 5557.2519)
    ))
    ; P1047 -- see feature_dimensions_mm.csv
    ("03_FRAMES_DOORS" 0 (
      (12778.626 4412.2137) (12594.3053 4412.2137) (12566.0 4412.2137) (12456.9008 4412.2137) (12428.5954 4412.2137)
      (12319.4962 4412.2137) (12291.1908 4412.2137) (12099.2366 4412.2137) (12099.2366 3832.0611)
    ))
    ; P1048 -- see feature_dimensions_mm.csv
    ("03_FRAMES_DOORS" 0 (
      (12153.0382 5679.3893) (12158.7786 5679.3893)
    ))
    ; P1049 -- see feature_dimensions_mm.csv
    ("03_FRAMES_DOORS" 0 (
      (12778.626 4473.2824) (12885.4962 4473.2824) (12885.4962 5282.4427) (12882.4733 5312.7634) (12873.6794 5341.8779)
      (12859.542 5369.8168) (12840.458 5396.5649) (12816.855 5422.1374) (12789.145 5446.5496) (12757.7405 5469.8015)
      (12723.0534 5491.9084) (12685.5115 5512.8702) (12645.5115 5532.687) (12603.4962 5551.374) (12559.8473 5568.9313)
      (12515.0076 5585.374) (12469.374 5600.7176) (12423.3588 5614.9466) (12377.4046 5628.0916) (12331.9084 5640.1374)
      (12287.2672 5651.1145) (12243.9237 5661.0076) (12202.2901 5669.8473) (12162.7634 5677.6183) (12153.0382 5679.3893)
    ))
    ; P1050 -- see feature_dimensions_mm.csv
    ("03_FRAMES_DOORS" 0 (
      (12173.4198 2155.7252) (12154.5802 2122.5954)
    ))
    ; P1051 -- see feature_dimensions_mm.csv
    ("03_FRAMES_DOORS" 0 (
      (12992.3664 4473.2824) (12992.3664 5374.0458) (12988.9466 5405.4809) (12979.0229 5435.6794) (12963.0382 5464.6565)
      (12941.4962 5492.3969) (12914.8244 5518.916) (12883.5267 5544.229) (12848.0458 5568.3511) (12808.8702 5591.2672)
      (12766.458 5613.0076) (12721.2824 5633.5573) (12673.8015 5652.9313) (12624.5038 5671.145) (12573.8473 5688.1985)
      (12522.3053 5704.1069) (12470.3359 5718.8702) (12418.4122 5732.5038) (12367.0076 5744.9924) (12316.5954 5756.3664)
      (12267.6336 5766.6412) (12220.5954 5775.8015) (12180.7176 5782.9924)
    ))
    ; P1052 -- see feature_dimensions_mm.csv
    ("03_FRAMES_DOORS" 0 (
      (13251.9084 656.4885) (13251.9084 1865.0382) (13250.7328 1898.8244) (13247.2061 1932.4733) (13241.3435 1965.8321)
      (13233.1756 1998.7481) (13222.7328 2031.1145) (13210.0763 2062.7481) (13195.2214 2093.542) (13178.2748 2123.3588)
      (13159.2824 2152.0611) (13138.3359 2179.542) (13115.5115 2205.6794) (13090.9313 2230.3511) (13064.6718 2253.4656)
      (13036.8702 2274.916) (13007.6489 2294.6107) (12977.0992 2312.458) (12945.374 2328.3969) (12912.626 2342.3511)
      (12878.9618 2354.2595) (12844.5344 2364.0763) (12809.5115 2371.7557) (12799.5725 2373.2977) (12795.1145 2351.145)
      (12609.4656 2351.145) (12605.0076 2373.2977) (12595.0687 2371.7557) (12560.0458 2364.0763) (12525.6183 2354.2595)
      (12491.9542 2342.3511) (12459.2061 2328.3969) (12427.4809 2312.458) (12396.9313 2294.6107) (12367.7099 2274.916)
      (12339.9084 2253.4656) (12313.6489 2230.3511) (12289.0687 2205.6794) (12266.2443 2179.542) (12245.2977 2152.0611)
      (12226.3053 2123.3588) (12209.3588 2093.542) (12194.5038 2062.7481) (12193.8321 2061.0687)
    ))
    ; P1053 -- see feature_dimensions_mm.csv
    ("03_FRAMES_DOORS" 0 (
      (12198.4733 1862.5954) (12198.4733 656.4885)
    ))
    ; P1054 -- see feature_dimensions_mm.csv
    ("03_FRAMES_DOORS" 0 (
      (12247.2977 2028.0611) (12239.6641 2008.9924) (12230.3817 1980.229) (12223.1298 1950.9618) (12217.9237 1921.313)
      (12214.7939 1891.4046) (12213.7405 1861.374) (12213.7405 656.4885) (13190.8397 656.4885)
    ))
    ; P1055 -- see feature_dimensions_mm.csv
    ("03_FRAMES_DOORS" 0 (
      (13190.8397 656.4885) (13190.8397 1861.374) (13189.7863 1891.4046) (13186.6565 1921.313) (13181.4504 1950.9618)
      (13174.1985 1980.229) (13164.916 2008.9924) (13153.6489 2037.1145) (13140.458 2064.4885) (13125.3893 2090.9924)
      (13108.5038 2116.5191) (13089.8779 2140.9466) (13069.6031 2164.1679) (13047.7405 2186.1069) (13024.4122 2206.6412)
      (12999.6947 2225.7099) (12973.7099 2243.2214) (12946.5649 2259.084) (12918.3664 2273.2519) (12889.2519 2285.6489)
      (12859.3282 2296.2443) (12828.7328 2304.9618) (12797.6031 2311.7863) (12766.0611 2316.687) (12734.2443 2319.6336)
      (12702.2901 2320.6107) (12670.3359 2319.6336) (12638.5191 2316.687) (12606.9771 2311.7863) (12575.8473 2304.9618)
      (12545.2519 2296.2443) (12515.3282 2285.6489) (12486.2137 2273.2519) (12458.0153 2259.084) (12430.8702 2243.2214)
      (12404.8855 2225.7099) (12380.1679 2206.6412) (12356.8397 2186.1069) (12334.9771 2164.1679) (12314.7023 2140.9466)
      (12296.0763 2116.5191) (12279.1908 2090.9924) (12264.1221 2064.4885) (12262.4733 2061.0687)
    ))
    ; P1056 -- see feature_dimensions_mm.csv
    ("03_FRAMES_DOORS" 0 (
      (12363.0076 2346.0) (12330.5344 2324.1221)
    ))
    ; P1057 -- see feature_dimensions_mm.csv
    ("03_FRAMES_DOORS" 0 (
      (12421.2061 5487.374) (12416.4427 5489.0229) (12384.8702 5498.9924)
    ))
    ; P1058 -- see feature_dimensions_mm.csv
    ("03_FRAMES_DOORS" 0 (
      (12432.1832 2383.542) (12396.9466 2365.8473)
    ))
    ; P1059 -- see feature_dimensions_mm.csv
    ("03_FRAMES_DOORS" 0 (
      (12534.3511 2961.8321) (12534.3511 2809.1603) (12412.2137 2809.1603) (12412.2137 2961.8321)
    ))
    ; P1060 -- see feature_dimensions_mm.csv
    ("03_FRAMES_DOORS" 0 (
      (12615.7252 5404.5649) (12604.5649 5410.9313) (12581.6031 5422.5496) (12569.7557 5428.5344) (12533.6031 5444.9618)
      (12533.1756 5445.145) (12495.1908 5460.7634) (12472.1374 5469.4046) (12456.1527 5475.3893)
    ))
    ; P1061 -- see feature_dimensions_mm.csv
    ("03_FRAMES_DOORS" 0 (
      (12592.9466 2433.2366) (12583.145 2431.7252)
    ))
    ; P1062 -- see feature_dimensions_mm.csv
    ("03_FRAMES_DOORS" 0 (
      (12588.5954 4473.2824) (12778.626 4473.2824)
    ))
    ; P1063 -- see feature_dimensions_mm.csv
    ("03_FRAMES_DOORS" 0 (
      (12667.4351 5372.6565) (12658.1679 5378.687) (12637.2366 5392.3053)
    ))
    ; P1064 -- see feature_dimensions_mm.csv
    ("03_FRAMES_DOORS" 0 (
      (12718.8855 5330.2901) (12694.7634 5351.9847) (12685.0992 5359.2824)
    ))
    ; P1065 -- see feature_dimensions_mm.csv
    ("03_FRAMES_DOORS" 0 (
      (12778.626 4473.2824) (12778.626 5206.1069) (12776.0 5233.0534) (12768.3511 5258.9466) (12756.0305 5283.771)
      (12739.4198 5307.542) (12727.0382 5321.2519)
    ))
    ; P1066 -- see feature_dimensions_mm.csv
    ("03_FRAMES_DOORS" 0 (
      (12885.4962 4412.2137) (12839.6947 4412.2137) (12809.1603 4412.2137) (12778.626 4412.2137)
    ))
    ; P1067 -- see feature_dimensions_mm.csv
    ("03_FRAMES_DOORS" 0 (
      (12778.626 4412.2137) (12778.626 3832.0611) (12809.1603 3832.0611)
    ))
    ; P1068 -- see feature_dimensions_mm.csv
    ("03_FRAMES_DOORS" 0 (
      (12972.3969 2383.542) (12935.9847 2399.0534) (12898.5954 2412.2901) (12860.3511 2423.1908) (12821.4351 2431.7252)
      (12811.6336 2433.2366)
    ))
    ; P1069 -- see feature_dimensions_mm.csv
    ("03_FRAMES_DOORS" 0 (
      (12839.6947 3832.0611) (12885.4962 3832.0611)
    ))
    ; P1070 -- see feature_dimensions_mm.csv
    ("03_FRAMES_DOORS" 0 (
      (12885.4962 3832.0611) (12992.3664 3832.0611) (12992.3664 4412.2137) (12885.4962 4412.2137)
    ))
    ; P1071 -- see feature_dimensions_mm.csv
    ("03_FRAMES_DOORS" 0 (
      (12885.4962 3832.0611) (12885.4962 4412.2137)
    ))
    ; P1072 -- see feature_dimensions_mm.csv
    ("03_FRAMES_DOORS" 0 (
      (13041.5725 2346.0) (13007.6336 2365.8473)
    ))
    ; P1073 -- see feature_dimensions_mm.csv
    ("03_FRAMES_DOORS" 0 (
      (13231.1603 2155.7252) (13210.0611 2187.6183) (13186.7786 2218.1527) (13161.4351 2247.1908) (13134.1069 2274.6107)
      (13104.9466 2300.2901)
    ))
    ; P1074 -- see feature_dimensions_mm.csv
    ("03_FRAMES_DOORS" 0 (
      (13190.8397 656.4885) (13251.9084 656.4885)
    ))
    ; P1075 -- see feature_dimensions_mm.csv
    ("03_FRAMES_DOORS" 0 (
      (13293.3588 2012.4427) (13236.6412 2061.0687) (13277.4198 2061.0687) (13266.4885 2088.3817) (13250.0 2122.5954)
    ))
    ; P1076 -- see feature_dimensions_mm.csv
    ("03_FRAMES_DOORS" 0 (
      (13251.9084 656.4885) (13282.4427 656.4885) (13282.4427 1862.5954) (13312.9771 1862.5954)
    ))
    ; P1077 -- see feature_dimensions_mm.csv
    ("03_FRAMES_DOORS" 0 (
      (13312.9771 1862.5954) (13312.9771 1868.7023) (13311.6641 1906.2443) (13307.7557 1943.6336) (13301.2366 1980.687)
      (13300.2443 1984.7328)
    ))
    ; P1078 -- see feature_dimensions_mm.csv
    ("03_FRAMES_DOORS" 0 (
      (13557.2519 1862.5954) (13389.313 1862.5954) (13312.9771 1862.5954)
    ))
    ; P1079 -- see feature_dimensions_mm.csv
    ("03_FRAMES_DOORS" 1 (
      (1206.1069 7465.6489) (1389.313 7465.6489) (1389.313 7114.5038) (1206.1069 7114.5038)
    ))
    ; P1080 -- see feature_dimensions_mm.csv
    ("03_FRAMES_DOORS" 1 (
      (1251.9084 9267.1756) (1358.7786 9267.1756) (1358.7786 8992.3664) (1251.9084 8992.3664)
    ))
    ; P1081 -- see feature_dimensions_mm.csv
    ("03_FRAMES_DOORS" 1 (
      (1473.2824 1847.3282) (1490.0763 1847.3282) (1490.0763 671.7557) (1473.2824 671.7557)
    ))
    ; P1082 -- see feature_dimensions_mm.csv
    ("03_FRAMES_DOORS" 1 (
      (1511.4504 1847.3282) (1528.2443 1847.3282) (1528.2443 671.7557) (1511.4504 671.7557)
    ))
    ; P1083 -- see feature_dimensions_mm.csv
    ("03_FRAMES_DOORS" 1 (
      (1549.6183 1847.3282) (1566.4122 1847.3282) (1566.4122 671.7557) (1549.6183 671.7557)
    ))
    ; P1084 -- see feature_dimensions_mm.csv
    ("03_FRAMES_DOORS" 1 (
      (1587.7863 1847.3282) (1604.5802 1847.3282) (1604.5802 671.7557) (1587.7863 671.7557)
    ))
    ; P1085 -- see feature_dimensions_mm.csv
    ("03_FRAMES_DOORS" 1 (
      (1625.9542 1847.3282) (1642.7481 1847.3282) (1642.7481 671.7557) (1625.9542 671.7557)
    ))
    ; P1086 -- see feature_dimensions_mm.csv
    ("03_FRAMES_DOORS" 1 (
      (1664.1221 1847.3282) (1680.916 1847.3282) (1680.916 671.7557) (1664.1221 671.7557)
    ))
    ; P1087 -- see feature_dimensions_mm.csv
    ("03_FRAMES_DOORS" 1 (
      (1694.6565 7465.6489) (1877.8626 7465.6489) (1877.8626 7114.5038) (1694.6565 7114.5038)
    ))
    ; P1088 -- see feature_dimensions_mm.csv
    ("03_FRAMES_DOORS" 1 (
      (1740.458 9267.1756) (1847.3282 9267.1756) (1847.3282 8992.3664) (1740.458 8992.3664)
    ))
    ; P1089 -- see feature_dimensions_mm.csv
    ("03_FRAMES_DOORS" 1 (
      (2167.9389 7465.6489) (2351.145 7465.6489) (2351.145 7114.5038) (2167.9389 7114.5038)
    ))
    ; P1090 -- see feature_dimensions_mm.csv
    ("03_FRAMES_DOORS" 1 (
      (2229.0076 9267.1756) (2335.8779 9267.1756) (2335.8779 8992.3664) (2229.0076 8992.3664)
    ))
    ; P1091 -- see feature_dimensions_mm.csv
    ("03_FRAMES_DOORS" 1 (
      (2656.4885 7465.6489) (2839.6947 7465.6489) (2839.6947 7114.5038) (2656.4885 7114.5038)
    ))
    ; P1092 -- see feature_dimensions_mm.csv
    ("03_FRAMES_DOORS" 1 (
      (2717.5573 9267.1756) (2824.4275 9267.1756) (2824.4275 8992.3664) (2717.5573 8992.3664)
    ))
    ; P1093 -- see feature_dimensions_mm.csv
    ("03_FRAMES_DOORS" 1 (
      (2862.5954 1847.3282) (2879.3893 1847.3282) (2879.3893 671.7557) (2862.5954 671.7557)
    ))
    ; P1094 -- see feature_dimensions_mm.csv
    ("03_FRAMES_DOORS" 1 (
      (2900.7634 1847.3282) (2917.5573 1847.3282) (2917.5573 671.7557) (2900.7634 671.7557)
    ))
    ; P1095 -- see feature_dimensions_mm.csv
    ("03_FRAMES_DOORS" 1 (
      (2938.9313 1847.3282) (2955.7252 1847.3282) (2955.7252 671.7557) (2938.9313 671.7557)
    ))
    ; P1096 -- see feature_dimensions_mm.csv
    ("03_FRAMES_DOORS" 1 (
      (2977.0992 1847.3282) (2993.8931 1847.3282) (2993.8931 671.7557) (2977.0992 671.7557)
    ))
    ; P1097 -- see feature_dimensions_mm.csv
    ("03_FRAMES_DOORS" 1 (
      (3015.2672 1847.3282) (3032.0611 1847.3282) (3032.0611 671.7557) (3015.2672 671.7557)
    ))
    ; P1098 -- see feature_dimensions_mm.csv
    ("03_FRAMES_DOORS" 1 (
      (3053.4351 1847.3282) (3070.229 1847.3282) (3070.229 671.7557) (3053.4351 671.7557)
    ))
    ; P1099 -- see feature_dimensions_mm.csv
    ("03_FRAMES_DOORS" 1 (
      (3129.771 7465.6489) (3312.9771 7465.6489) (3312.9771 7114.5038) (3129.771 7114.5038)
    ))
    ; P1100 -- see feature_dimensions_mm.csv
    ("03_FRAMES_DOORS" 1 (
      (3206.1069 9267.1756) (3312.9771 9267.1756) (3312.9771 8992.3664) (3206.1069 8992.3664)
    ))
    ; P1101 -- see feature_dimensions_mm.csv
    ("03_FRAMES_DOORS" 1 (
      (3389.313 1938.9313) (3389.9542 1956.9008) (3391.8626 1974.7939) (3395.0382 1992.5496) (3399.4504 2010.0611)
      (3405.1145 2027.2672) (3411.9695 2044.0916) (3420.0153 2060.4733) (3429.2061 2076.3359) (3439.4809 2091.6031)
      (3450.8397 2106.229) (3463.1908 2120.1221) (3476.5038 2133.2519) (3490.7328 2145.542) (3505.7863 2156.9466)
      (3521.6183 2167.4198) (3538.1679 2176.916) (3555.3435 2185.4046) (3573.0992 2192.8244) (3591.3282 2199.1603)
      (3609.9695 2204.3817) (3628.9466 2208.458) (3648.1679 2211.3893) (3667.5573 2213.145) (3687.0229 2213.7405)
      (3706.4885 2213.145) (3725.8779 2211.3893) (3745.0992 2208.458) (3764.0763 2204.3817) (3782.7176 2199.1603)
      (3800.9466 2192.8244) (3818.7023 2185.4046) (3835.8779 2176.916) (3852.4275 2167.4198) (3868.2595 2156.9466)
      (3883.313 2145.542) (3897.542 2133.2519) (3910.855 2120.1221) (3923.2061 2106.229) (3934.5649 2091.6031)
      (3944.855 2076.3359) (3954.0305 2060.4733) (3962.0763 2044.0916) (3968.9313 2027.2672) (3974.5954 2010.0611)
      (3979.0076 1992.5496) (3982.1832 1974.7939) (3984.0916 1956.9008) (3984.7328 1938.9313) (3984.7328 1435.1145)
      (3389.313 1435.1145)
    ))
    ; P1102 -- see feature_dimensions_mm.csv
    ("03_FRAMES_DOORS" 1 (
      (3389.313 1282.4427) (3984.7328 1282.4427) (3984.7328 610.687) (3389.313 610.687)
    ))
    ; P1103 -- see feature_dimensions_mm.csv
    ("03_FRAMES_DOORS" 1 (
      (3465.6489 1908.3969) (3466.1221 1922.3817) (3467.542 1936.2901) (3469.9084 1950.0916) (3473.1908 1963.7099)
      (3477.4046 1977.0992) (3482.5038 1990.1985) (3488.4733 2002.9313) (3495.313 2015.2672) (3502.9618 2027.145)
      (3511.3893 2038.5191) (3520.5802 2049.3282) (3530.4885 2059.5267) (3541.0534 2069.0992) (3552.2595 2077.9695)
      (3564.0305 2086.1221) (3576.3359 2093.4962) (3589.1145 2100.0916) (3602.3053 2105.8626) (3615.8626 2110.7939)
      (3629.7252 2114.855) (3643.8321 2118.0305) (3658.1221 2120.3053) (3672.5496 2121.6794) (3687.0229 2122.1374)
      (3701.4962 2121.6794) (3715.9237 2120.3053) (3730.2137 2118.0305) (3744.3206 2114.855) (3758.1832 2110.7939)
      (3771.7405 2105.8626) (3784.9313 2100.0916) (3797.7099 2093.4962) (3810.0153 2086.1221) (3821.7863 2077.9695)
      (3832.9924 2069.0992) (3843.5573 2059.5267) (3853.4656 2049.3282) (3862.6565 2038.5191) (3871.084 2027.145)
      (3878.7328 2015.2672) (3885.5725 2002.9313) (3891.542 1990.1985) (3896.6412 1977.0992) (3900.855 1963.7099)
      (3904.1374 1950.0916) (3906.5038 1936.2901) (3907.9237 1922.3817) (3908.3969 1908.3969) (3908.3969 1511.4504)
      (3465.6489 1511.4504)
    ))
    ; P1104 -- see feature_dimensions_mm.csv
    ("03_FRAMES_DOORS" 1 (
      (3465.6489 1206.1069) (3908.3969 1206.1069) (3908.3969 687.0229) (3465.6489 687.0229)
    ))
    ; P1105 -- see feature_dimensions_mm.csv
    ("03_FRAMES_DOORS" 1 (
      (3618.3206 7465.6489) (3801.5267 7465.6489) (3801.5267 7114.5038) (3618.3206 7114.5038)
    ))
    ; P1106 -- see feature_dimensions_mm.csv
    ("03_FRAMES_DOORS" 1 (
      (3694.6565 9267.1756) (3801.5267 9267.1756) (3801.5267 8992.3664) (3694.6565 8992.3664)
    ))
    ; P1107 -- see feature_dimensions_mm.csv
    ("03_FRAMES_DOORS" 1 (
      (4091.6031 7465.6489) (4274.8092 7465.6489) (4274.8092 7114.5038) (4091.6031 7114.5038)
    ))
    ; P1108 -- see feature_dimensions_mm.csv
    ("03_FRAMES_DOORS" 1 (
      (4282.4427 1847.3282) (4299.2366 1847.3282) (4299.2366 671.7557) (4282.4427 671.7557)
    ))
    ; P1109 -- see feature_dimensions_mm.csv
    ("03_FRAMES_DOORS" 1 (
      (4320.6107 1847.3282) (4337.4046 1847.3282) (4337.4046 671.7557) (4320.6107 671.7557)
    ))
    ; P1110 -- see feature_dimensions_mm.csv
    ("03_FRAMES_DOORS" 1 (
      (4358.7786 1847.3282) (4375.5725 1847.3282) (4375.5725 671.7557) (4358.7786 671.7557)
    ))
    ; P1111 -- see feature_dimensions_mm.csv
    ("03_FRAMES_DOORS" 1 (
      (4396.9466 1847.3282) (4413.7405 1847.3282) (4413.7405 671.7557) (4396.9466 671.7557)
    ))
    ; P1112 -- see feature_dimensions_mm.csv
    ("03_FRAMES_DOORS" 1 (
      (4435.1145 1847.3282) (4451.9084 1847.3282) (4451.9084 671.7557) (4435.1145 671.7557)
    ))
    ; P1113 -- see feature_dimensions_mm.csv
    ("03_FRAMES_DOORS" 1 (
      (4473.2824 1847.3282) (4490.0763 1847.3282) (4490.0763 671.7557) (4473.2824 671.7557)
    ))
    ; P1114 -- see feature_dimensions_mm.csv
    ("03_FRAMES_DOORS" 1 (
      (4580.1527 7465.6489) (4763.3588 7465.6489) (4763.3588 7114.5038) (4580.1527 7114.5038)
    ))
    ; P1115 -- see feature_dimensions_mm.csv
    ("03_FRAMES_DOORS" 1 (
      (5297.7099 5297.7099) (5298.5038 5324.6718) (5300.916 5351.5115) (5304.9008 5378.1221) (5310.458 5404.3969)
      (5317.5573 5430.2137) (5326.1832 5455.4504) (5336.2901 5480.0305) (5347.8168 5503.8168) (5360.7481 5526.7176)
      (5375.0076 5548.6565) (5390.5344 5569.4962) (5407.2672 5589.1908) (5425.1298 5607.6336) (5444.0458 5624.7481)
      (5463.9542 5640.458) (5484.7328 5654.7023) (5506.3206 5667.4198) (5528.6107 5678.5496) (5551.5267 5688.0458)
      (5574.9466 5695.8779) (5598.7786 5702.0) (5622.9313 5706.3969) (5647.2977 5709.0382) (5671.7557 5709.9237)
      (5696.2137 5709.0382) (5720.5802 5706.3969) (5744.7328 5702.0) (5768.5649 5695.8779) (5791.9847 5688.0458)
      (5814.9008 5678.5496) (5837.1908 5667.4198) (5858.7786 5654.7023) (5879.5573 5640.458) (5899.4656 5624.7481)
      (5918.3817 5607.6336) (5936.2443 5589.1908) (5952.9771 5569.4962) (5968.5038 5548.6565) (5982.7634 5526.7176)
      (5995.6947 5503.8168) (6007.2214 5480.0305) (6017.3282 5455.4504) (6025.9542 5430.2137) (6033.0534 5404.3969)
      (6038.6107 5378.1221) (6042.5954 5351.5115) (6045.0076 5324.6718) (6045.8015 5297.7099) (6045.8015 1129.771)
      (5297.7099 1129.771)
    ))
    ; P1116 -- see feature_dimensions_mm.csv
    ("03_FRAMES_DOORS" 1 (
      (5358.7786 5251.9084) (5359.4504 5276.8702) (5361.4504 5301.7252) (5364.7939 5326.3664) (5369.4504 5350.687)
      (5375.3893 5374.5954) (5382.5954 5397.9695) (5391.0534 5420.7176) (5400.7023 5442.7481) (5411.5267 5463.9542)
      (5423.4504 5484.2595) (5436.4427 5503.5725) (5450.4427 5521.8015) (5465.3893 5538.8702) (5481.2214 5554.7176)
      (5497.8779 5569.2672) (5515.2672 5582.458) (5533.3282 5594.229) (5551.9847 5604.5344) (5571.145 5613.3282)
      (5590.7481 5620.5802) (5610.7023 5626.2595) (5630.9008 5630.3206) (5651.2824 5632.7634) (5671.7557 5633.5878)
      (5692.229 5632.7634) (5712.6107 5630.3206) (5732.8092 5626.2595) (5752.7634 5620.5802) (5772.3664 5613.3282)
      (5791.5267 5604.5344) (5810.1832 5594.229) (5828.2443 5582.458) (5845.6336 5569.2672) (5862.2901 5554.7176)
      (5878.1221 5538.8702) (5893.0687 5521.8015) (5907.0687 5503.5725) (5920.0611 5484.2595) (5931.9847 5463.9542)
      (5942.8092 5442.7481) (5952.458 5420.7176) (5960.916 5397.9695) (5968.1221 5374.5954) (5974.0611 5350.687)
      (5978.7176 5326.3664) (5982.0611 5301.7252) (5984.0611 5276.8702) (5984.7328 5251.9084) (5984.7328 1206.1069)
      (5358.7786 1206.1069)
    ))
    ; P1117 -- see feature_dimensions_mm.csv
    ("03_FRAMES_DOORS" 1 (
      (6335.8779 5297.7099) (6337.0229 5324.6718) (6340.4427 5351.5115) (6346.1527 5378.1221) (6354.0916 5404.3969)
      (6364.229 5430.2137) (6376.5496 5455.4504) (6390.9771 5480.0305) (6407.4656 5503.8168) (6425.9389 5526.7176)
      (6446.3053 5548.6565) (6468.4885 5569.4962) (6492.3817 5589.1908) (6517.9084 5607.6336) (6544.9313 5624.7481)
      (6573.3588 5640.458) (6603.0534 5654.7023) (6633.8931 5667.4198) (6665.7405 5678.5496) (6698.4733 5688.0458)
      (6731.9237 5695.8779) (6765.9847 5702.0) (6800.4885 5706.3969) (6835.2824 5709.0382) (6870.229 5709.9237)
      (6905.1756 5709.0382) (6939.9695 5706.3969) (6974.4733 5702.0) (7008.5344 5695.8779) (7041.9847 5688.0458)
      (7074.7176 5678.5496) (7106.5649 5667.4198) (7137.4046 5654.7023) (7167.0992 5640.458) (7195.5267 5624.7481)
      (7222.5496 5607.6336) (7248.0763 5589.1908) (7271.9695 5569.4962) (7294.1527 5548.6565) (7314.5191 5526.7176)
      (7332.9924 5503.8168) (7349.4809 5480.0305) (7363.9084 5455.4504) (7376.229 5430.2137) (7386.3664 5404.3969)
      (7394.3053 5378.1221) (7400.0153 5351.5115) (7403.4351 5324.6718) (7404.5802 5297.7099) (7404.5802 1129.771)
      (6335.8779 1129.771)
    ))
    ; P1118 -- see feature_dimensions_mm.csv
    ("03_FRAMES_DOORS" 1 (
      (6396.9466 5251.9084) (6397.9542 5276.8702) (6400.9924 5301.7252) (6406.0458 5326.3664) (6413.0687 5350.687)
      (6422.0611 5374.5954) (6432.9771 5397.9695) (6445.7557 5420.7176) (6460.3511 5442.7481) (6476.7023 5463.9542)
      (6494.7481 5484.2595) (6514.3969 5503.5725) (6535.5725 5521.8015) (6558.1679 5538.8702) (6582.1069 5554.7176)
      (6607.2824 5569.2672) (6633.5878 5582.458) (6660.9008 5594.229) (6689.1145 5604.5344) (6718.0916 5613.3282)
      (6747.7405 5620.5802) (6777.8931 5626.2595) (6808.458 5630.3206) (6839.2824 5632.7634) (6870.229 5633.5878)
      (6901.1908 5632.7634) (6932.0 5630.3206) (6962.5649 5626.2595) (6992.7176 5620.5802) (7022.3664 5613.3282)
      (7051.3435 5604.5344) (7079.5573 5594.229) (7106.8702 5582.458) (7133.1756 5569.2672) (7158.3511 5554.7176)
      (7182.2901 5538.8702) (7204.8855 5521.8015) (7226.0611 5503.5725) (7245.7099 5484.2595) (7263.7557 5463.9542)
      (7280.1069 5442.7481) (7294.7023 5420.7176) (7307.4809 5397.9695) (7318.3969 5374.5954) (7327.3893 5350.687)
      (7334.4122 5326.3664) (7339.4656 5301.7252) (7342.5038 5276.8702) (7343.5115 5251.9084) (7343.5115 1206.1069)
      (6396.9466 1206.1069)
    ))
    ; P1119 -- see feature_dimensions_mm.csv
    ("03_FRAMES_DOORS" 1 (
      (7694.6565 5297.7099) (7695.4504 5324.6718) (7697.8626 5351.5115) (7701.8473 5378.1221) (7707.4046 5404.3969)
      (7714.5038 5430.2137) (7723.1298 5455.4504) (7733.2366 5480.0305) (7744.7634 5503.8168) (7757.6947 5526.7176)
      (7771.9542 5548.6565) (7787.4809 5569.4962) (7804.2137 5589.1908) (7822.0763 5607.6336) (7840.9924 5624.7481)
      (7860.9008 5640.458) (7881.6794 5654.7023) (7903.2672 5667.4198) (7925.5573 5678.5496) (7948.4733 5688.0458)
      (7971.8931 5695.8779) (7995.7252 5702.0) (8019.8779 5706.3969) (8044.2443 5709.0382) (8068.7023 5709.9237)
      (8093.1603 5709.0382) (8117.5267 5706.3969) (8141.6794 5702.0) (8165.5115 5695.8779) (8188.9313 5688.0458)
      (8211.8473 5678.5496) (8234.1374 5667.4198) (8255.7252 5654.7023) (8276.5038 5640.458) (8296.4122 5624.7481)
      (8315.3282 5607.6336) (8333.1908 5589.1908) (8349.9237 5569.4962) (8365.4504 5548.6565) (8379.7099 5526.7176)
      (8392.6412 5503.8168) (8404.1679 5480.0305) (8414.2748 5455.4504) (8422.9008 5430.2137) (8430.0 5404.3969)
      (8435.5573 5378.1221) (8439.542 5351.5115) (8441.9542 5324.6718) (8442.7481 5297.7099) (8442.7481 1129.771)
      (7694.6565 1129.771)
    ))
    ; P1120 -- see feature_dimensions_mm.csv
    ("03_FRAMES_DOORS" 1 (
      (7755.7252 5251.9084) (7756.3969 5276.8702) (7758.3969 5301.7252) (7761.7405 5326.3664) (7766.3969 5350.687)
      (7772.3359 5374.5954) (7779.542 5397.9695) (7788.0 5420.7176) (7797.6489 5442.7481) (7808.4733 5463.9542)
      (7820.3969 5484.2595) (7833.3893 5503.5725) (7847.3893 5521.8015) (7862.3359 5538.8702) (7878.1679 5554.7176)
      (7894.8244 5569.2672) (7912.2137 5582.458) (7930.2748 5594.229) (7948.9313 5604.5344) (7968.0916 5613.3282)
      (7987.6947 5620.5802) (8007.6489 5626.2595) (8027.8473 5630.3206) (8048.229 5632.7634) (8068.7023 5633.5878)
      (8089.1756 5632.7634) (8109.5573 5630.3206) (8129.7557 5626.2595) (8149.7099 5620.5802) (8169.313 5613.3282)
      (8188.4733 5604.5344) (8207.1298 5594.229) (8225.1908 5582.458) (8242.5802 5569.2672) (8259.2366 5554.7176)
      (8275.0687 5538.8702) (8290.0153 5521.8015) (8304.0153 5503.5725) (8317.0076 5484.2595) (8328.9313 5463.9542)
      (8339.7557 5442.7481) (8349.4046 5420.7176) (8357.8626 5397.9695) (8365.0687 5374.5954) (8371.0076 5350.687)
      (8375.6641 5326.3664) (8379.0076 5301.7252) (8381.0076 5276.8702) (8381.6794 5251.9084) (8381.6794 1206.1069)
      (7755.7252 1206.1069)
    ))
    ; P1121 -- see feature_dimensions_mm.csv
    ("03_FRAMES_DOORS" 1 (
      (8839.6947 2320.6107) (8839.6947 396.9466) (8839.6947 335.8779) (10152.6718 335.8779) (10152.6718 396.9466)
      (10152.6718 2320.6107) (10150.2595 2359.9084) (10143.2672 2397.6641) (10132.0 2433.8626) (10116.8092 2468.5496)
      (10098.0153 2501.7099) (10075.9389 2533.3435) (10050.9313 2563.4962) (10023.313 2592.1374) (9993.4198 2619.2977)
      (9961.5725 2644.9924) (9928.1069 2669.2214) (9893.3588 2691.9847) (9857.6489 2713.2977) (9821.313 2733.1908)
      (9784.6718 2751.6336) (9748.0763 2768.6718) (9711.8473 2784.3053) (9676.3053 2798.5191) (9641.8015 2811.3588)
      (9608.6412 2822.8092) (9577.1603 2832.8855) (9547.7099 2841.5878) (9520.6107 2848.9466) (9496.1832 2854.9618)
      (9471.7557 2848.9466) (9444.6565 2841.5878) (9415.2061 2832.8855) (9383.7252 2822.8092) (9350.5649 2811.3588)
      (9316.0611 2798.5191) (9280.5191 2784.3053) (9244.2901 2768.6718) (9207.6947 2751.6336) (9171.0534 2733.1908)
      (9134.7176 2713.2977) (9099.0076 2691.9847) (9064.2595 2669.2214) (9030.7939 2644.9924) (8998.9466 2619.2977)
      (8969.0534 2592.1374) (8941.4351 2563.4962) (8916.4275 2533.3435) (8894.3511 2501.7099) (8875.5573 2468.5496)
      (8860.3664 2433.8626) (8849.0992 2397.6641) (8842.1069 2359.9084)
    ))
    ; P1122 -- see feature_dimensions_mm.csv
    ("03_FRAMES_DOORS" 1 (
      (8992.3664 7480.916) (8992.3664 7114.5038) (9175.5725 7114.5038) (9175.5725 7480.916)
    ))
    ; P1123 -- see feature_dimensions_mm.csv
    ("03_FRAMES_DOORS" 1 (
      (9022.9008 1938.9313) (9023.9084 1966.8855) (9026.9466 1994.7328) (9032.0 2022.3359) (9039.0229 2049.5725)
      (9048.0153 2076.3359) (9058.9313 2102.5191) (9071.7099 2128.0) (9086.3053 2152.6718) (9102.6565 2176.4275)
      (9120.7023 2199.1603) (9140.3511 2220.7939) (9161.5267 2241.2061) (9184.1221 2260.3359) (9208.0611 2278.0763)
      (9233.2366 2294.3664) (9259.542 2309.145) (9286.855 2322.3206) (9315.0687 2333.8779) (9344.0458 2343.7252)
      (9373.6947 2351.8473) (9403.8473 2358.1985) (9434.4122 2362.7481) (9465.2366 2365.4962) (9496.1832 2366.4122)
      (9527.145 2365.4962) (9557.9542 2362.7481) (9588.5191 2358.1985) (9618.6718 2351.8473) (9648.3206 2343.7252)
      (9677.2977 2333.8779) (9705.5115 2322.3206) (9732.8244 2309.145) (9759.1298 2294.3664) (9784.3053 2278.0763)
      (9808.2443 2260.3359) (9830.8397 2241.2061) (9852.0153 2220.7939) (9871.6641 2199.1603) (9889.7099 2176.4275)
      (9906.0611 2152.6718) (9920.6565 2128.0) (9933.4351 2102.5191) (9944.3511 2076.3359) (9953.3435 2049.5725)
      (9960.3664 2022.3359) (9965.4198 1994.7328) (9968.458 1966.8855) (9969.4656 1938.9313) (9969.4656 427.4809)
      (9022.9008 427.4809)
    ))
    ; P1124 -- see feature_dimensions_mm.csv
    ("03_FRAMES_DOORS" 1 (
      (9099.2366 1908.3969) (9100.0916 1932.3664) (9102.626 1956.229) (9106.8702 1979.8779) (9112.7634 2003.2366)
      (9120.3053 2026.1832) (9129.4504 2048.6107) (9140.1679 2070.458) (9152.4122 2091.6031) (9166.1374 2111.9695)
      (9181.2672 2131.4504) (9197.7405 2149.9847) (9215.4962 2167.4962) (9234.458 2183.8779) (9254.5344 2199.084)
      (9275.6489 2213.0534) (9297.7099 2225.7252) (9320.6107 2237.0229) (9344.2748 2246.916) (9368.5954 2255.3588)
      (9393.4504 2262.3206) (9418.7481 2267.771) (9444.3664 2271.6794) (9470.229 2274.0305) (9496.1832 2274.8092)
      (9522.1374 2274.0305) (9548.0 2271.6794) (9573.6183 2267.771) (9598.916 2262.3206) (9623.771 2255.3588)
      (9648.0916 2246.916) (9671.7557 2237.0229) (9694.6565 2225.7252) (9716.7176 2213.0534) (9737.8321 2199.084)
      (9757.9084 2183.8779) (9776.8702 2167.4962) (9794.626 2149.9847) (9811.0992 2131.4504) (9826.229 2111.9695)
      (9839.9542 2091.6031) (9852.1985 2070.458) (9862.916 2048.6107) (9872.0611 2026.1832) (9879.6031 2003.2366)
      (9885.4962 1979.8779) (9889.7405 1956.229) (9892.2748 1932.3664) (9893.1298 1908.3969) (9893.1298 473.2824)
      (9099.2366 473.2824)
    ))
    ; P1125 -- see feature_dimensions_mm.csv
    ("03_FRAMES_DOORS" 1 (
      (9206.1069 1282.4427) (9786.2595 1282.4427) (9786.2595 625.9542) (9206.1069 625.9542)
    ))
    ; P1126 -- see feature_dimensions_mm.csv
    ("03_FRAMES_DOORS" 1 (
      (9221.374 1862.5954) (9221.9695 1879.5725) (9223.7252 1896.4733) (9226.6565 1913.2366) (9230.7328 1929.771)
      (9235.9542 1946.0153) (9242.2901 1961.9237) (9249.7099 1977.3893) (9258.1985 1992.3664) (9267.6947 2006.7939)
      (9278.1679 2020.5954) (9289.5725 2033.7252) (9301.8626 2046.1221) (9314.9924 2057.7252) (9328.8855 2068.5038)
      (9343.5115 2078.3969) (9358.7786 2087.3588) (9374.6412 2095.374) (9391.0229 2102.3817) (9407.8473 2108.3664)
      (9425.0534 2113.2977) (9442.5649 2117.145) (9460.3206 2119.9237) (9478.2137 2121.5878) (9496.1832 2122.1374)
      (9514.1527 2121.5878) (9532.0458 2119.9237) (9549.8015 2117.145) (9567.313 2113.2977) (9584.5191 2108.3664)
      (9601.3435 2102.3817) (9617.7252 2095.374) (9633.5878 2087.3588) (9648.855 2078.3969) (9663.4809 2068.5038)
      (9677.374 2057.7252) (9690.5038 2046.1221) (9702.7939 2033.7252) (9714.1985 2020.5954) (9724.6718 2006.7939)
      (9734.1679 1992.3664) (9742.6565 1977.3893) (9750.0763 1961.9237) (9756.4122 1946.0153) (9761.6336 1929.771)
      (9765.7099 1913.2366) (9768.6412 1896.4733) (9770.3969 1879.5725) (9770.9924 1862.5954) (9770.9924 1435.1145)
      (9221.374 1435.1145)
    ))
    ; P1127 -- see feature_dimensions_mm.csv
    ("03_FRAMES_DOORS" 1 (
      (9282.4427 1832.0611) (9282.9008 1846.0458) (9284.2748 1859.9542) (9286.5496 1873.7557) (9289.7252 1887.374)
      (9293.7863 1900.7634) (9298.7176 1913.8626) (9304.4885 1926.5954) (9311.084 1938.9313) (9318.458 1950.8092)
      (9326.6107 1962.1832) (9335.4809 1972.9924) (9345.0534 1983.1908) (9355.2519 1992.7634) (9366.0611 2001.6336)
      (9377.4351 2009.7863) (9389.313 2017.1603) (9401.6489 2023.7557) (9414.3817 2029.5267) (9427.4809 2034.458)
      (9440.8702 2038.5191) (9454.4885 2041.6947) (9468.2901 2043.9695) (9482.1985 2045.3435) (9496.1832 2045.8015)
      (9510.1679 2045.3435) (9524.0763 2043.9695) (9537.8779 2041.6947) (9551.4962 2038.5191) (9564.8855 2034.458)
      (9577.9847 2029.5267) (9590.7176 2023.7557) (9603.0534 2017.1603) (9614.9313 2009.7863) (9626.3053 2001.6336)
      (9637.1145 1992.7634) (9647.313 1983.1908) (9656.8855 1972.9924) (9665.7557 1962.1832) (9673.9084 1950.8092)
      (9681.2824 1938.9313) (9687.8779 1926.5954) (9693.6489 1913.8626) (9698.5802 1900.7634) (9702.6412 1887.374)
      (9705.8168 1873.7557) (9708.0916 1859.9542) (9709.4656 1846.0458) (9709.9237 1832.0611) (9709.9237 1511.4504)
      (9282.4427 1511.4504)
    ))
    ; P1128 -- see feature_dimensions_mm.csv
    ("03_FRAMES_DOORS" 1 (
      (9282.4427 1206.1069) (9709.9237 1206.1069) (9709.9237 702.2901) (9282.4427 702.2901)
    ))
    ; P1129 -- see feature_dimensions_mm.csv
    ("03_FRAMES_DOORS" 1 (
      (9404.5802 7480.916) (9404.5802 7114.5038) (9587.7863 7114.5038) (9587.7863 7480.916)
    ))
    ; P1130 -- see feature_dimensions_mm.csv
    ("03_FRAMES_DOORS" 1 (
      (9465.6489 4412.2137) (9465.6489 3832.0611) (9473.2824 3832.0611) (9473.2824 4412.2137)
    ))
    ; P1131 -- see feature_dimensions_mm.csv
    ("03_FRAMES_DOORS" 1 (
      (9816.7939 7480.916) (9816.7939 7114.5038) (10000.0 7114.5038) (10000.0 7480.916)
    ))
    ; P1132 -- see feature_dimensions_mm.csv
    ("03_FRAMES_DOORS" 1 (
      (10519.084 7465.6489) (10702.2901 7465.6489) (10702.2901 7114.5038) (10519.084 7114.5038)
    ))
    ; P1133 -- see feature_dimensions_mm.csv
    ("03_FRAMES_DOORS" 1 (
      (10618.3206 1847.3282) (10635.1145 1847.3282) (10635.1145 671.7557) (10618.3206 671.7557)
    ))
    ; P1134 -- see feature_dimensions_mm.csv
    ("03_FRAMES_DOORS" 1 (
      (10656.4885 1847.3282) (10673.2824 1847.3282) (10673.2824 671.7557) (10656.4885 671.7557)
    ))
    ; P1135 -- see feature_dimensions_mm.csv
    ("03_FRAMES_DOORS" 1 (
      (10694.6565 1847.3282) (10711.4504 1847.3282) (10711.4504 671.7557) (10694.6565 671.7557)
    ))
    ; P1136 -- see feature_dimensions_mm.csv
    ("03_FRAMES_DOORS" 1 (
      (10732.8244 1847.3282) (10749.6183 1847.3282) (10749.6183 671.7557) (10732.8244 671.7557)
    ))
    ; P1137 -- see feature_dimensions_mm.csv
    ("03_FRAMES_DOORS" 1 (
      (10770.9924 1847.3282) (10787.7863 1847.3282) (10787.7863 671.7557) (10770.9924 671.7557)
    ))
    ; P1138 -- see feature_dimensions_mm.csv
    ("03_FRAMES_DOORS" 1 (
      (10809.1603 1847.3282) (10825.9542 1847.3282) (10825.9542 671.7557) (10809.1603 671.7557)
    ))
    ; P1139 -- see feature_dimensions_mm.csv
    ("03_FRAMES_DOORS" 1 (
      (11007.6336 7465.6489) (11190.8397 7465.6489) (11190.8397 7114.5038) (11007.6336 7114.5038)
    ))
    ; P1140 -- see feature_dimensions_mm.csv
    ("03_FRAMES_DOORS" 1 (
      (11496.1832 7465.6489) (11679.3893 7465.6489) (11679.3893 7114.5038) (11496.1832 7114.5038)
    ))
    ; P1141 -- see feature_dimensions_mm.csv
    ("03_FRAMES_DOORS" 1 (
      (11961.8321 1847.3282) (11978.626 1847.3282) (11978.626 671.7557) (11961.8321 671.7557)
    ))
    ; P1142 -- see feature_dimensions_mm.csv
    ("03_FRAMES_DOORS" 1 (
      (11984.7328 7465.6489) (12167.9389 7465.6489) (12167.9389 7114.5038) (11984.7328 7114.5038)
    ))
    ; P1143 -- see feature_dimensions_mm.csv
    ("03_FRAMES_DOORS" 1 (
      (12000.0 1847.3282) (12016.7939 1847.3282) (12016.7939 671.7557) (12000.0 671.7557)
    ))
    ; P1144 -- see feature_dimensions_mm.csv
    ("03_FRAMES_DOORS" 1 (
      (12022.9008 4412.2137) (12022.9008 3832.0611) (12045.8015 3832.0611) (12045.8015 4412.2137)
    ))
    ; P1145 -- see feature_dimensions_mm.csv
    ("03_FRAMES_DOORS" 1 (
      (12038.1679 1847.3282) (12054.9618 1847.3282) (12054.9618 671.7557) (12038.1679 671.7557)
    ))
    ; P1146 -- see feature_dimensions_mm.csv
    ("03_FRAMES_DOORS" 1 (
      (12076.3359 1847.3282) (12093.1298 1847.3282) (12093.1298 671.7557) (12076.3359 671.7557)
    ))
    ; P1147 -- see feature_dimensions_mm.csv
    ("03_FRAMES_DOORS" 1 (
      (12114.5038 1847.3282) (12131.2977 1847.3282) (12131.2977 671.7557) (12114.5038 671.7557)
    ))
    ; P1148 -- see feature_dimensions_mm.csv
    ("03_FRAMES_DOORS" 1 (
      (12152.6718 1847.3282) (12169.4656 1847.3282) (12169.4656 671.7557) (12152.6718 671.7557)
    ))
    ; P1149 -- see feature_dimensions_mm.csv
    ("03_FRAMES_DOORS" 1 (
      (12473.2824 7465.6489) (12656.4885 7465.6489) (12656.4885 7114.5038) (12473.2824 7114.5038)
    ))
    ; P1150 -- see feature_dimensions_mm.csv
    ("03_FRAMES_DOORS" 1 (
      (12702.2901 3099.2366) (12824.4275 3099.2366) (12824.4275 2961.8321) (12824.4275 2809.1603) (12702.2901 2809.1603)
      (12702.2901 2961.8321)
    ))
    ; P1151 -- see feature_dimensions_mm.csv
    ("03_FRAMES_DOORS" 1 (
      (12961.8321 7465.6489) (13145.0382 7465.6489) (13145.0382 7114.5038) (12961.8321 7114.5038)
    ))
    ; P1152 -- see feature_dimensions_mm.csv
    ("03_FRAMES_DOORS" 1 (
      (12992.3664 3099.2366) (13114.5038 3099.2366) (13114.5038 2961.8321) (13114.5038 2809.1603) (12992.3664 2809.1603)
      (12992.3664 2961.8321)
    ))
    ; P1153 -- see feature_dimensions_mm.csv
    ("03_FRAMES_DOORS" 1 (
      (13320.6107 1847.3282) (13337.4046 1847.3282) (13337.4046 671.7557) (13320.6107 671.7557)
    ))
    ; P1154 -- see feature_dimensions_mm.csv
    ("03_FRAMES_DOORS" 1 (
      (13358.7786 1847.3282) (13375.5725 1847.3282) (13375.5725 671.7557) (13358.7786 671.7557)
    ))
    ; P1155 -- see feature_dimensions_mm.csv
    ("03_FRAMES_DOORS" 1 (
      (13396.9466 1847.3282) (13413.7405 1847.3282) (13413.7405 671.7557) (13396.9466 671.7557)
    ))
    ; P1156 -- see feature_dimensions_mm.csv
    ("03_FRAMES_DOORS" 1 (
      (13435.1145 7465.6489) (13618.3206 7465.6489) (13618.3206 7114.5038) (13435.1145 7114.5038)
    ))
    ; P1157 -- see feature_dimensions_mm.csv
    ("03_FRAMES_DOORS" 1 (
      (13435.1145 1847.3282) (13451.9084 1847.3282) (13451.9084 671.7557) (13435.1145 671.7557)
    ))
    ; P1158 -- see feature_dimensions_mm.csv
    ("03_FRAMES_DOORS" 1 (
      (13473.2824 1847.3282) (13490.0763 1847.3282) (13490.0763 671.7557) (13473.2824 671.7557)
    ))
    ; P1159 -- see feature_dimensions_mm.csv
    ("03_FRAMES_DOORS" 1 (
      (13511.4504 1847.3282) (13528.2443 1847.3282) (13528.2443 671.7557) (13511.4504 671.7557)
    ))
    ; P1160 -- see feature_dimensions_mm.csv
    ("04_GLAZING_SHUTTERS" 0 (
      (900.7634 5541.9847) (900.7634 5206.1069) (900.7634 5129.771) (900.7634 5053.4351) (900.7634 4961.8321)
      (900.7634 4870.229) (900.7634 4534.3511) (900.7634 4458.0153) (900.7634 4381.6794) (900.7634 4290.0763)
      (900.7634 4198.4733) (900.7634 4167.9389) (854.9618 4167.9389) (503.8168 4167.9389) (213.7405 4167.9389)
      (213.7405 4198.4733) (213.7405 4290.0763) (213.7405 4381.6794) (213.7405 4458.0153) (213.7405 4534.3511)
      (213.7405 4870.229) (213.7405 4961.8321)
    ))
    ; P1161 -- see feature_dimensions_mm.csv
    ("04_GLAZING_SHUTTERS" 0 (
      (340.855 6357.1908) (526.7176 6229.0076) (486.8092 6198.1221)
    ))
    ; P1162 -- see feature_dimensions_mm.csv
    ("04_GLAZING_SHUTTERS" 0 (
      (340.855 6357.1908) (320.6107 6305.3435) (486.8092 6198.1221)
    ))
    ; P1163 -- see feature_dimensions_mm.csv
    ("04_GLAZING_SHUTTERS" 0 (
      (360.9618 6408.6412) (305.3435 6381.6794) (340.855 6357.1908)
    ))
    ; P1164 -- see feature_dimensions_mm.csv
    ("04_GLAZING_SHUTTERS" 0 (
      (360.9618 6408.6412) (340.855 6357.1908)
    ))
    ; P1165 -- see feature_dimensions_mm.csv
    ("04_GLAZING_SHUTTERS" 0 (
      (340.855 4677.8015) (526.7176 4549.6183) (486.8092 4518.7328)
    ))
    ; P1166 -- see feature_dimensions_mm.csv
    ("04_GLAZING_SHUTTERS" 0 (
      (340.855 4677.8015) (320.6107 4625.9542) (486.8092 4518.7328)
    ))
    ; P1167 -- see feature_dimensions_mm.csv
    ("04_GLAZING_SHUTTERS" 0 (
      (360.9618 4729.2519) (305.3435 4702.2901) (340.855 4677.8015)
    ))
    ; P1168 -- see feature_dimensions_mm.csv
    ("04_GLAZING_SHUTTERS" 0 (
      (360.9618 4729.2519) (340.855 4677.8015)
    ))
    ; P1169 -- see feature_dimensions_mm.csv
    ("04_GLAZING_SHUTTERS" 0 (
      (753.542 6408.6412) (603.0534 6793.8931) (824.4275 7236.6412) (824.4275 7419.8473) (290.0763 7419.8473)
      (290.0763 7236.6412) (511.4504 6793.8931) (360.9618 6408.6412)
    ))
    ; P1170 -- see feature_dimensions_mm.csv
    ("04_GLAZING_SHUTTERS" 0 (
      (753.542 6408.6412) (557.2519 6503.8168) (360.9618 6408.6412)
    ))
    ; P1171 -- see feature_dimensions_mm.csv
    ("04_GLAZING_SHUTTERS" 0 (
      (753.542 4729.2519) (603.0534 5114.5038) (824.4275 5557.2519) (824.4275 5740.458) (290.0763 5740.458)
      (290.0763 5557.2519) (511.4504 5114.5038) (360.9618 4729.2519)
    ))
    ; P1172 -- see feature_dimensions_mm.csv
    ("04_GLAZING_SHUTTERS" 0 (
      (753.542 4729.2519) (557.2519 4824.4275) (360.9618 4729.2519)
    ))
    ; P1173 -- see feature_dimensions_mm.csv
    ("04_GLAZING_SHUTTERS" 0 (
      (486.8092 6198.1221) (557.2519 6152.6718) (627.6947 6198.1221)
    ))
    ; P1174 -- see feature_dimensions_mm.csv
    ("04_GLAZING_SHUTTERS" 0 (
      (486.8092 6198.1221) (290.0763 6045.8015) (290.0763 5923.6641) (824.4275 5923.6641) (824.4275 6045.8015)
      (627.6947 6198.1221)
    ))
    ; P1175 -- see feature_dimensions_mm.csv
    ("04_GLAZING_SHUTTERS" 0 (
      (486.8092 4518.7328) (557.2519 4473.2824) (627.6947 4518.7328)
    ))
    ; P1176 -- see feature_dimensions_mm.csv
    ("04_GLAZING_SHUTTERS" 0 (
      (486.8092 4518.7328) (290.0763 4366.4122) (290.0763 4244.2748) (824.4275 4244.2748) (824.4275 4366.4122)
      (627.6947 4518.7328)
    ))
    ; P1177 -- see feature_dimensions_mm.csv
    ("04_GLAZING_SHUTTERS" 0 (
      (627.6947 6198.1221) (587.7863 6229.0076) (773.6489 6357.1908)
    ))
    ; P1178 -- see feature_dimensions_mm.csv
    ("04_GLAZING_SHUTTERS" 0 (
      (627.6947 6198.1221) (793.8931 6305.3435) (773.6489 6357.1908)
    ))
    ; P1179 -- see feature_dimensions_mm.csv
    ("04_GLAZING_SHUTTERS" 0 (
      (627.6947 4518.7328) (587.7863 4549.6183) (773.6489 4677.8015)
    ))
    ; P1180 -- see feature_dimensions_mm.csv
    ("04_GLAZING_SHUTTERS" 0 (
      (627.6947 4518.7328) (793.8931 4625.9542) (773.6489 4677.8015)
    ))
    ; P1181 -- see feature_dimensions_mm.csv
    ("04_GLAZING_SHUTTERS" 0 (
      (773.6489 6357.1908) (809.1603 6381.6794) (753.542 6408.6412)
    ))
    ; P1182 -- see feature_dimensions_mm.csv
    ("04_GLAZING_SHUTTERS" 0 (
      (773.6489 6357.1908) (753.542 6408.6412)
    ))
    ; P1183 -- see feature_dimensions_mm.csv
    ("04_GLAZING_SHUTTERS" 0 (
      (773.6489 4677.8015) (809.1603 4702.2901) (753.542 4729.2519)
    ))
    ; P1184 -- see feature_dimensions_mm.csv
    ("04_GLAZING_SHUTTERS" 0 (
      (773.6489 4677.8015) (753.542 4729.2519)
    ))
    ; P1185 -- see feature_dimensions_mm.csv
    ("04_GLAZING_SHUTTERS" 0 (
      (854.9618 7496.1832) (900.7634 7496.1832) (900.7634 7221.374) (900.7634 7145.0382) (900.7634 7068.7023)
      (900.7634 6977.0992)
    ))
    ; P1186 -- see feature_dimensions_mm.csv
    ("04_GLAZING_SHUTTERS" 0 (
      (2732.8244 1099.2366) (1786.2595 1099.2366)
    ))
    ; P1187 -- see feature_dimensions_mm.csv
    ("04_GLAZING_SHUTTERS" 0 (
      (1786.2595 977.0992) (1786.2595 1099.2366)
    ))
    ; P1188 -- see feature_dimensions_mm.csv
    ("04_GLAZING_SHUTTERS" 0 (
      (1786.2595 1099.2366) (1786.2595 1221.374) (2732.8244 1221.374) (2732.8244 1099.2366)
    ))
    ; P1189 -- see feature_dimensions_mm.csv
    ("04_GLAZING_SHUTTERS" 0 (
      (2732.8244 977.0992) (1786.2595 977.0992)
    ))
    ; P1190 -- see feature_dimensions_mm.csv
    ("04_GLAZING_SHUTTERS" 0 (
      (1786.2595 961.8321) (1786.2595 977.0992)
    ))
    ; P1191 -- see feature_dimensions_mm.csv
    ("04_GLAZING_SHUTTERS" 0 (
      (1786.2595 961.8321) (2732.8244 961.8321)
    ))
    ; P1192 -- see feature_dimensions_mm.csv
    ("04_GLAZING_SHUTTERS" 0 (
      (1786.2595 839.6947) (1786.2595 961.8321)
    ))
    ; P1193 -- see feature_dimensions_mm.csv
    ("04_GLAZING_SHUTTERS" 0 (
      (2732.8244 839.6947) (1786.2595 839.6947)
    ))
    ; P1194 -- see feature_dimensions_mm.csv
    ("04_GLAZING_SHUTTERS" 0 (
      (1786.2595 824.4275) (1786.2595 839.6947)
    ))
    ; P1195 -- see feature_dimensions_mm.csv
    ("04_GLAZING_SHUTTERS" 0 (
      (1786.2595 824.4275) (2732.8244 824.4275)
    ))
    ; P1196 -- see feature_dimensions_mm.csv
    ("04_GLAZING_SHUTTERS" 0 (
      (1786.2595 702.2901) (1786.2595 824.4275)
    ))
    ; P1197 -- see feature_dimensions_mm.csv
    ("04_GLAZING_SHUTTERS" 0 (
      (2732.8244 702.2901) (1786.2595 702.2901)
    ))
    ; P1198 -- see feature_dimensions_mm.csv
    ("04_GLAZING_SHUTTERS" 0 (
      (2732.8244 702.2901) (2732.8244 671.7557) (1786.2595 671.7557) (1786.2595 702.2901)
    ))
    ; P1199 -- see feature_dimensions_mm.csv
    ("04_GLAZING_SHUTTERS" 0 (
      (2715.2061 1885.4809) (2716.5802 1872.4275) (2717.5573 1844.2748) (2717.5573 1778.626) (2717.5573 1702.2901)
      (2717.5573 1592.2901) (2717.5573 1536.626) (2717.5573 1236.6412) (1801.5267 1236.6412) (1801.5267 1536.626)
      (1801.5267 1592.2901) (1801.5267 1702.2901) (1801.5267 1778.626) (1801.5267 1844.2748) (1802.5038 1872.4275)
      (1803.8779 1885.4809)
    ))
    ; P1200 -- see feature_dimensions_mm.csv
    ("04_GLAZING_SHUTTERS" 0 (
      (1816.9618 1955.0229) (1817.1298 1955.7099) (1825.8321 1982.6718) (1836.3969 2009.0382) (1848.7634 2034.7023)
      (1862.8855 2059.542) (1878.7176 2083.4656) (1896.1679 2106.3664) (1915.1908 2128.1527) (1935.6794 2148.7023)
      (1957.5573 2167.9695) (1966.1527 2174.5954)
    ))
    ; P1201 -- see feature_dimensions_mm.csv
    ("04_GLAZING_SHUTTERS" 0 (
      (1982.5954 2187.0992) (2005.084 2202.2443) (2030.5344 2217.1298) (2056.9618 2230.4122) (2084.2748 2242.0305)
      (2112.3206 2251.9542) (2140.9924 2260.1374) (2170.1832 2266.5344) (2199.7557 2271.1298) (2229.5878 2273.8931)
      (2259.542 2274.8092) (2289.4962 2273.8931) (2319.3282 2271.1298) (2348.9008 2266.5344) (2378.0916 2260.1374)
      (2406.7634 2251.9542) (2434.8244 2242.0305) (2462.1221 2230.4122) (2488.5496 2217.1298) (2514.0 2202.2443)
      (2536.4885 2187.0992)
    ))
    ; P1202 -- see feature_dimensions_mm.csv
    ("04_GLAZING_SHUTTERS" 0 (
      (2552.9313 2174.5954) (2561.5267 2167.9695) (2583.4046 2148.7023) (2603.8931 2128.1527) (2622.916 2106.3664)
      (2640.3664 2083.4656) (2656.1985 2059.542) (2670.3206 2034.7023) (2682.687 2009.0382) (2693.2519 1982.6718)
      (2701.9542 1955.7099) (2702.1221 1955.0229)
    ))
    ; P1203 -- see feature_dimensions_mm.csv
    ("04_GLAZING_SHUTTERS" 0 (
      (2708.7634 1928.2748) (2713.6336 1900.4733)
    ))
    ; P1204 -- see feature_dimensions_mm.csv
    ("04_GLAZING_SHUTTERS" 0 (
      (2732.8244 1099.2366) (2732.8244 977.0992)
    ))
    ; P1205 -- see feature_dimensions_mm.csv
    ("04_GLAZING_SHUTTERS" 0 (
      (2732.8244 977.0992) (2732.8244 961.8321)
    ))
    ; P1206 -- see feature_dimensions_mm.csv
    ("04_GLAZING_SHUTTERS" 0 (
      (2732.8244 961.8321) (2732.8244 839.6947)
    ))
    ; P1207 -- see feature_dimensions_mm.csv
    ("04_GLAZING_SHUTTERS" 0 (
      (2732.8244 839.6947) (2732.8244 824.4275)
    ))
    ; P1208 -- see feature_dimensions_mm.csv
    ("04_GLAZING_SHUTTERS" 0 (
      (2732.8244 824.4275) (2732.8244 702.2901)
    ))
    ; P1209 -- see feature_dimensions_mm.csv
    ("04_GLAZING_SHUTTERS" 0 (
      (5435.1145 4519.084) (5923.6641 4519.084)
    ))
    ; P1210 -- see feature_dimensions_mm.csv
    ("04_GLAZING_SHUTTERS" 0 (
      (5435.1145 2366.4122) (5435.1145 4519.084)
    ))
    ; P1211 -- see feature_dimensions_mm.csv
    ("04_GLAZING_SHUTTERS" 0 (
      (5435.1145 4519.084) (5435.1145 5236.6412) (5436.0153 5260.2137) (5438.6107 5282.8702) (5442.8092 5304.5954)
      (5448.458 5325.4046) (5455.4504 5345.2977) (5463.6641 5364.2901) (5472.9618 5382.3664) (5483.2519 5399.5573)
      (5494.3664 5415.8626) (5506.2137 5431.2672) (5518.6718 5445.8015) (5531.6031 5459.4656) (5544.8855 5472.2595)
      (5558.4122 5484.1832) (5572.0458 5495.2519) (5585.6641 5505.4809) (5599.145 5514.855) (5612.3664 5523.3893)
      (5625.2061 5531.084) (5637.542 5537.9542) (5649.2519 5544.0) (5660.2137 5549.2366) (5670.3053 5553.6489)
      (5679.3893 5557.2519) (5688.4733 5553.6489) (5698.5649 5549.2366) (5709.5267 5544.0) (5721.2366 5537.9542)
      (5733.5725 5531.084) (5746.4122 5523.3893) (5759.6336 5514.855) (5773.1145 5505.4809) (5786.7328 5495.2519)
      (5800.3664 5484.1832) (5813.8931 5472.2595) (5827.1756 5459.4656) (5840.1069 5445.8015) (5852.5649 5431.2672)
      (5864.4122 5415.8626) (5875.5267 5399.5573) (5885.8168 5382.3664) (5895.1145 5364.2901) (5903.3282 5345.2977)
      (5910.3206 5325.4046) (5915.9695 5304.5954) (5920.1679 5282.8702) (5922.7634 5260.2137) (5923.6641 5236.6412)
      (5923.6641 4519.084)
    ))
    ; P1212 -- see feature_dimensions_mm.csv
    ("04_GLAZING_SHUTTERS" 0 (
      (5450.3817 2366.4122) (5435.1145 2366.4122)
    ))
    ; P1213 -- see feature_dimensions_mm.csv
    ("04_GLAZING_SHUTTERS" 0 (
      (5923.6641 2366.4122) (5923.6641 1236.6412) (5435.1145 1236.6412) (5435.1145 2366.4122)
    ))
    ; P1214 -- see feature_dimensions_mm.csv
    ("04_GLAZING_SHUTTERS" 0 (
      (5908.3969 2366.4122) (5450.3817 2366.4122)
    ))
    ; P1215 -- see feature_dimensions_mm.csv
    ("04_GLAZING_SHUTTERS" 0 (
      (5908.3969 2366.4122) (5908.3969 2355.7252) (5450.3817 2355.7252) (5450.3817 2366.4122)
    ))
    ; P1216 -- see feature_dimensions_mm.csv
    ("04_GLAZING_SHUTTERS" 0 (
      (5450.3817 2366.4122) (5450.3817 2427.4809) (5908.3969 2427.4809) (5908.3969 2366.4122)
    ))
    ; P1217 -- see feature_dimensions_mm.csv
    ("04_GLAZING_SHUTTERS" 0 (
      (5923.6641 2366.4122) (5908.3969 2366.4122)
    ))
    ; P1218 -- see feature_dimensions_mm.csv
    ("04_GLAZING_SHUTTERS" 0 (
      (5923.6641 4519.084) (5923.6641 2366.4122)
    ))
    ; P1219 -- see feature_dimensions_mm.csv
    ("04_GLAZING_SHUTTERS" 0 (
      (6412.2137 4519.084) (7328.2443 4519.084)
    ))
    ; P1220 -- see feature_dimensions_mm.csv
    ("04_GLAZING_SHUTTERS" 0 (
      (6412.2137 2366.4122) (6412.2137 4519.084)
    ))
    ; P1221 -- see feature_dimensions_mm.csv
    ("04_GLAZING_SHUTTERS" 0 (
      (6412.2137 4519.084) (6412.2137 5236.6412) (6413.8931 5260.2137) (6418.7786 5282.8702) (6426.6412 5304.5954)
      (6437.2366 5325.4046) (6450.3511 5345.2977) (6465.7405 5364.2901) (6483.1908 5382.3664) (6502.458 5399.5573)
      (6523.313 5415.8626) (6545.542 5431.2672) (6568.8855 5445.8015) (6593.1298 5459.4656) (6618.0458 5472.2595)
      (6643.3893 5484.1832) (6668.9466 5495.2519) (6694.4885 5505.4809) (6719.771 5514.855) (6744.5649 5523.3893)
      (6768.6412 5531.084) (6791.771 5537.9542) (6813.7252 5544.0) (6834.2748 5549.2366) (6853.1908 5553.6489)
      (6870.229 5557.2519) (6887.2672 5553.6489) (6906.1832 5549.2366) (6926.7328 5544.0) (6948.687 5537.9542)
      (6971.8168 5531.084) (6995.8931 5523.3893) (7020.687 5514.855) (7045.9695 5505.4809) (7071.5115 5495.2519)
      (7097.0687 5484.1832) (7122.4122 5472.2595) (7147.3282 5459.4656) (7171.5725 5445.8015) (7194.916 5431.2672)
      (7217.145 5415.8626) (7238.0 5399.5573) (7257.2672 5382.3664) (7274.7176 5364.2901) (7290.1069 5345.2977)
      (7303.2214 5325.4046) (7313.8168 5304.5954) (7321.6794 5282.8702) (7326.5649 5260.2137) (7328.2443 5236.6412)
      (7328.2443 4519.084)
    ))
    ; P1222 -- see feature_dimensions_mm.csv
    ("04_GLAZING_SHUTTERS" 0 (
      (6427.4809 2366.4122) (6412.2137 2366.4122)
    ))
    ; P1223 -- see feature_dimensions_mm.csv
    ("04_GLAZING_SHUTTERS" 0 (
      (7328.2443 2366.4122) (7328.2443 1236.6412) (6412.2137 1236.6412) (6412.2137 2366.4122)
    ))
    ; P1224 -- see feature_dimensions_mm.csv
    ("04_GLAZING_SHUTTERS" 0 (
      (7312.9771 2366.4122) (6427.4809 2366.4122)
    ))
    ; P1225 -- see feature_dimensions_mm.csv
    ("04_GLAZING_SHUTTERS" 0 (
      (7312.9771 2366.4122) (7312.9771 2355.7252) (6427.4809 2355.7252) (6427.4809 2366.4122)
    ))
    ; P1226 -- see feature_dimensions_mm.csv
    ("04_GLAZING_SHUTTERS" 0 (
      (6427.4809 2366.4122) (6427.4809 2427.4809) (7312.9771 2427.4809) (7312.9771 2366.4122)
    ))
    ; P1227 -- see feature_dimensions_mm.csv
    ("04_GLAZING_SHUTTERS" 0 (
      (7190.8397 2305.3435) (6549.6183 2305.3435)
    ))
    ; P1228 -- see feature_dimensions_mm.csv
    ("04_GLAZING_SHUTTERS" 0 (
      (6549.6183 2305.3435) (6656.4885 1938.9313) (6870.229 1770.9924)
    ))
    ; P1229 -- see feature_dimensions_mm.csv
    ("04_GLAZING_SHUTTERS" 0 (
      (6549.6183 2305.3435) (6458.0153 2305.3435) (6458.0153 1282.4427) (6870.229 1282.4427)
    ))
    ; P1230 -- see feature_dimensions_mm.csv
    ("04_GLAZING_SHUTTERS" 0 (
      (6870.229 1374.0458) (7083.9695 1572.5191) (6870.229 1770.9924)
    ))
    ; P1231 -- see feature_dimensions_mm.csv
    ("04_GLAZING_SHUTTERS" 0 (
      (6870.229 1770.9924) (6656.4885 1572.5191) (6870.229 1374.0458)
    ))
    ; P1232 -- see feature_dimensions_mm.csv
    ("04_GLAZING_SHUTTERS" 0 (
      (6870.229 1770.9924) (7083.9695 1938.9313) (7190.8397 2305.3435)
    ))
    ; P1233 -- see feature_dimensions_mm.csv
    ("04_GLAZING_SHUTTERS" 0 (
      (6870.229 1282.4427) (6870.229 1374.0458)
    ))
    ; P1234 -- see feature_dimensions_mm.csv
    ("04_GLAZING_SHUTTERS" 0 (
      (6870.229 1282.4427) (7282.4427 1282.4427) (7282.4427 2305.3435) (7190.8397 2305.3435)
    ))
    ; P1235 -- see feature_dimensions_mm.csv
    ("04_GLAZING_SHUTTERS" 0 (
      (7328.2443 2366.4122) (7312.9771 2366.4122)
    ))
    ; P1236 -- see feature_dimensions_mm.csv
    ("04_GLAZING_SHUTTERS" 0 (
      (7328.2443 4519.084) (7328.2443 2366.4122)
    ))
    ; P1237 -- see feature_dimensions_mm.csv
    ("04_GLAZING_SHUTTERS" 0 (
      (7832.0611 4519.084) (8305.3435 4519.084)
    ))
    ; P1238 -- see feature_dimensions_mm.csv
    ("04_GLAZING_SHUTTERS" 0 (
      (7832.0611 2366.4122) (7832.0611 4519.084)
    ))
    ; P1239 -- see feature_dimensions_mm.csv
    ("04_GLAZING_SHUTTERS" 0 (
      (7832.0611 4519.084) (7832.0611 5236.6412) (7832.9313 5260.2137) (7835.4504 5282.8702) (7839.5115 5304.5954)
      (7844.9924 5325.4046) (7851.771 5345.2977) (7859.7252 5364.2901) (7868.7328 5382.3664) (7878.687 5399.5573)
      (7889.4656 5415.8626) (7900.9466 5431.2672) (7913.0076 5445.8015) (7925.542 5459.4656) (7938.4122 5472.2595)
      (7951.5115 5484.1832) (7964.7023 5495.2519) (7977.9084 5505.4809) (7990.9618 5514.855) (8003.771 5523.3893)
      (8016.2137 5531.084) (8028.1679 5537.9542) (8039.5115 5544.0) (8050.1221 5549.2366) (8059.8931 5553.6489)
      (8068.7023 5557.2519) (8077.5115 5553.6489) (8087.2824 5549.2366) (8097.8931 5544.0) (8109.2366 5537.9542)
      (8121.1908 5531.084) (8133.6336 5523.3893) (8146.4427 5514.855) (8159.4962 5505.4809) (8172.7023 5495.2519)
      (8185.8931 5484.1832) (8198.9924 5472.2595) (8211.8779 5459.4656) (8224.3969 5445.8015) (8236.458 5431.2672)
      (8247.9389 5415.8626) (8258.7176 5399.5573) (8268.6718 5382.3664) (8277.6794 5364.2901) (8285.6336 5345.2977)
      (8292.4122 5325.4046) (8297.8931 5304.5954) (8301.9542 5282.8702) (8304.4733 5260.2137) (8305.3435 5236.6412)
      (8305.3435 4519.084)
    ))
    ; P1240 -- see feature_dimensions_mm.csv
    ("04_GLAZING_SHUTTERS" 0 (
      (7847.3282 2366.4122) (7832.0611 2366.4122)
    ))
    ; P1241 -- see feature_dimensions_mm.csv
    ("04_GLAZING_SHUTTERS" 0 (
      (8305.3435 2366.4122) (8305.3435 1236.6412) (7832.0611 1236.6412) (7832.0611 2366.4122)
    ))
    ; P1242 -- see feature_dimensions_mm.csv
    ("04_GLAZING_SHUTTERS" 0 (
      (8290.0763 2366.4122) (7847.3282 2366.4122)
    ))
    ; P1243 -- see feature_dimensions_mm.csv
    ("04_GLAZING_SHUTTERS" 0 (
      (8290.0763 2366.4122) (8290.0763 2355.7252) (7847.3282 2355.7252) (7847.3282 2366.4122)
    ))
    ; P1244 -- see feature_dimensions_mm.csv
    ("04_GLAZING_SHUTTERS" 0 (
      (7847.3282 2366.4122) (7847.3282 2427.4809) (8290.0763 2427.4809) (8290.0763 2366.4122)
    ))
    ; P1245 -- see feature_dimensions_mm.csv
    ("04_GLAZING_SHUTTERS" 0 (
      (8305.3435 2366.4122) (8290.0763 2366.4122)
    ))
    ; P1246 -- see feature_dimensions_mm.csv
    ("04_GLAZING_SHUTTERS" 0 (
      (8305.3435 4519.084) (8305.3435 2366.4122)
    ))
    ; P1247 -- see feature_dimensions_mm.csv
    ("04_GLAZING_SHUTTERS" 0 (
      (11832.0611 1099.2366) (10885.4962 1099.2366)
    ))
    ; P1248 -- see feature_dimensions_mm.csv
    ("04_GLAZING_SHUTTERS" 0 (
      (10885.4962 977.0992) (10885.4962 1099.2366)
    ))
    ; P1249 -- see feature_dimensions_mm.csv
    ("04_GLAZING_SHUTTERS" 0 (
      (10885.4962 1099.2366) (10885.4962 1221.374) (11832.0611 1221.374) (11832.0611 1099.2366)
    ))
    ; P1250 -- see feature_dimensions_mm.csv
    ("04_GLAZING_SHUTTERS" 0 (
      (11832.0611 977.0992) (10885.4962 977.0992)
    ))
    ; P1251 -- see feature_dimensions_mm.csv
    ("04_GLAZING_SHUTTERS" 0 (
      (10885.4962 961.8321) (10885.4962 977.0992)
    ))
    ; P1252 -- see feature_dimensions_mm.csv
    ("04_GLAZING_SHUTTERS" 0 (
      (10885.4962 961.8321) (11832.0611 961.8321)
    ))
    ; P1253 -- see feature_dimensions_mm.csv
    ("04_GLAZING_SHUTTERS" 0 (
      (10885.4962 839.6947) (10885.4962 961.8321)
    ))
    ; P1254 -- see feature_dimensions_mm.csv
    ("04_GLAZING_SHUTTERS" 0 (
      (11832.0611 839.6947) (10885.4962 839.6947)
    ))
    ; P1255 -- see feature_dimensions_mm.csv
    ("04_GLAZING_SHUTTERS" 0 (
      (10885.4962 824.4275) (10885.4962 839.6947)
    ))
    ; P1256 -- see feature_dimensions_mm.csv
    ("04_GLAZING_SHUTTERS" 0 (
      (10885.4962 824.4275) (11832.0611 824.4275)
    ))
    ; P1257 -- see feature_dimensions_mm.csv
    ("04_GLAZING_SHUTTERS" 0 (
      (10885.4962 702.2901) (10885.4962 824.4275)
    ))
    ; P1258 -- see feature_dimensions_mm.csv
    ("04_GLAZING_SHUTTERS" 0 (
      (11832.0611 702.2901) (10885.4962 702.2901)
    ))
    ; P1259 -- see feature_dimensions_mm.csv
    ("04_GLAZING_SHUTTERS" 0 (
      (11832.0611 702.2901) (11832.0611 671.7557) (10885.4962 671.7557) (10885.4962 702.2901)
    ))
    ; P1260 -- see feature_dimensions_mm.csv
    ("04_GLAZING_SHUTTERS" 0 (
      (10900.7634 1778.626) (10900.7634 1844.2748) (10901.7405 1872.4275) (10903.1145 1885.4809)
    ))
    ; P1261 -- see feature_dimensions_mm.csv
    ("04_GLAZING_SHUTTERS" 0 (
      (10900.7634 1592.2901) (10900.7634 1702.2901)
    ))
    ; P1262 -- see feature_dimensions_mm.csv
    ("04_GLAZING_SHUTTERS" 0 (
      (11816.7939 1536.626) (11816.7939 1236.6412) (10900.7634 1236.6412) (10900.7634 1536.626)
    ))
    ; P1263 -- see feature_dimensions_mm.csv
    ("04_GLAZING_SHUTTERS" 0 (
      (10916.1985 1955.0229) (10916.3664 1955.7099) (10925.0687 1982.6718) (10935.6336 2009.0382) (10948.0 2034.7023)
      (10962.1221 2059.542) (10977.9542 2083.4656) (10995.4046 2106.3664) (11014.4275 2128.1527) (11034.916 2148.7023)
      (11056.7939 2167.9695) (11065.3893 2174.5954)
    ))
    ; P1264 -- see feature_dimensions_mm.csv
    ("04_GLAZING_SHUTTERS" 0 (
      (11081.8321 2187.0992) (11104.3206 2202.2443) (11129.771 2217.1298) (11156.1985 2230.4122) (11183.5115 2242.0305)
      (11211.5573 2251.9542) (11240.229 2260.1374) (11269.4198 2266.5344) (11298.9924 2271.1298) (11328.8244 2273.8931)
      (11358.7786 2274.8092) (11388.7328 2273.8931) (11418.5649 2271.1298) (11448.1374 2266.5344) (11477.3282 2260.1374)
      (11506.0 2251.9542) (11534.0611 2242.0305) (11561.3588 2230.4122) (11587.7863 2217.1298) (11613.2366 2202.2443)
      (11635.7252 2187.0992)
    ))
    ; P1265 -- see feature_dimensions_mm.csv
    ("04_GLAZING_SHUTTERS" 0 (
      (11652.1679 2174.5954) (11660.7634 2167.9695) (11682.6412 2148.7023) (11703.1298 2128.1527) (11722.1527 2106.3664)
      (11739.6031 2083.4656) (11755.4351 2059.542) (11769.5573 2034.7023) (11781.9237 2009.0382) (11792.4885 1982.6718)
      (11801.1908 1955.7099) (11801.3588 1955.0229)
    ))
    ; P1266 -- see feature_dimensions_mm.csv
    ("04_GLAZING_SHUTTERS" 0 (
      (11808.0 1928.2748) (11812.8702 1900.4733)
    ))
    ; P1267 -- see feature_dimensions_mm.csv
    ("04_GLAZING_SHUTTERS" 0 (
      (11814.4427 1885.4809) (11815.8168 1872.4275) (11816.7939 1844.2748) (11816.7939 1778.626)
    ))
    ; P1268 -- see feature_dimensions_mm.csv
    ("04_GLAZING_SHUTTERS" 0 (
      (11816.7939 1702.2901) (11816.7939 1592.2901)
    ))
    ; P1269 -- see feature_dimensions_mm.csv
    ("04_GLAZING_SHUTTERS" 0 (
      (11832.0611 1099.2366) (11832.0611 977.0992)
    ))
    ; P1270 -- see feature_dimensions_mm.csv
    ("04_GLAZING_SHUTTERS" 0 (
      (11832.0611 977.0992) (11832.0611 961.8321)
    ))
    ; P1271 -- see feature_dimensions_mm.csv
    ("04_GLAZING_SHUTTERS" 0 (
      (11832.0611 961.8321) (11832.0611 839.6947)
    ))
    ; P1272 -- see feature_dimensions_mm.csv
    ("04_GLAZING_SHUTTERS" 0 (
      (11832.0611 839.6947) (11832.0611 824.4275)
    ))
    ; P1273 -- see feature_dimensions_mm.csv
    ("04_GLAZING_SHUTTERS" 0 (
      (11832.0611 824.4275) (11832.0611 702.2901)
    ))
    ; P1274 -- see feature_dimensions_mm.csv
    ("04_GLAZING_SHUTTERS" 0 (
      (13175.5725 1099.2366) (12229.0076 1099.2366)
    ))
    ; P1275 -- see feature_dimensions_mm.csv
    ("04_GLAZING_SHUTTERS" 0 (
      (12229.0076 977.0992) (12229.0076 1099.2366)
    ))
    ; P1276 -- see feature_dimensions_mm.csv
    ("04_GLAZING_SHUTTERS" 0 (
      (12229.0076 1099.2366) (12229.0076 1221.374) (13175.5725 1221.374) (13175.5725 1099.2366)
    ))
    ; P1277 -- see feature_dimensions_mm.csv
    ("04_GLAZING_SHUTTERS" 0 (
      (13175.5725 977.0992) (12229.0076 977.0992)
    ))
    ; P1278 -- see feature_dimensions_mm.csv
    ("04_GLAZING_SHUTTERS" 0 (
      (12229.0076 961.8321) (12229.0076 977.0992)
    ))
    ; P1279 -- see feature_dimensions_mm.csv
    ("04_GLAZING_SHUTTERS" 0 (
      (12229.0076 961.8321) (13175.5725 961.8321)
    ))
    ; P1280 -- see feature_dimensions_mm.csv
    ("04_GLAZING_SHUTTERS" 0 (
      (12229.0076 839.6947) (12229.0076 961.8321)
    ))
    ; P1281 -- see feature_dimensions_mm.csv
    ("04_GLAZING_SHUTTERS" 0 (
      (13175.5725 839.6947) (12229.0076 839.6947)
    ))
    ; P1282 -- see feature_dimensions_mm.csv
    ("04_GLAZING_SHUTTERS" 0 (
      (12229.0076 824.4275) (12229.0076 839.6947)
    ))
    ; P1283 -- see feature_dimensions_mm.csv
    ("04_GLAZING_SHUTTERS" 0 (
      (12229.0076 824.4275) (13175.5725 824.4275)
    ))
    ; P1284 -- see feature_dimensions_mm.csv
    ("04_GLAZING_SHUTTERS" 0 (
      (12229.0076 702.2901) (12229.0076 824.4275)
    ))
    ; P1285 -- see feature_dimensions_mm.csv
    ("04_GLAZING_SHUTTERS" 0 (
      (13175.5725 702.2901) (12229.0076 702.2901)
    ))
    ; P1286 -- see feature_dimensions_mm.csv
    ("04_GLAZING_SHUTTERS" 0 (
      (13175.5725 702.2901) (13175.5725 671.7557) (12229.0076 671.7557) (12229.0076 702.2901)
    ))
    ; P1287 -- see feature_dimensions_mm.csv
    ("04_GLAZING_SHUTTERS" 0 (
      (12246.626 1885.4809) (12245.2519 1872.4275) (12244.2748 1844.2748) (12244.2748 1778.626)
    ))
    ; P1288 -- see feature_dimensions_mm.csv
    ("04_GLAZING_SHUTTERS" 0 (
      (12244.2748 1702.2901) (12244.2748 1592.2901)
    ))
    ; P1289 -- see feature_dimensions_mm.csv
    ("04_GLAZING_SHUTTERS" 0 (
      (12244.2748 1536.626) (12244.2748 1236.6412) (13160.3053 1236.6412) (13160.3053 1536.626) (13160.3053 1592.2901)
      (13160.3053 1702.2901) (13160.3053 1778.626) (13160.3053 1844.2748) (13159.3282 1872.4275) (13157.9542 1885.4809)
    ))
    ; P1290 -- see feature_dimensions_mm.csv
    ("04_GLAZING_SHUTTERS" 0 (
      (12408.9008 2174.5954) (12400.3053 2167.9695) (12378.4275 2148.7023) (12357.9389 2128.1527) (12338.916 2106.3664)
      (12321.4656 2083.4656) (12305.6336 2059.542) (12291.5115 2034.7023) (12279.145 2009.0382) (12268.5802 1982.6718)
      (12259.8779 1955.7099) (12259.7099 1955.0229)
    ))
    ; P1291 -- see feature_dimensions_mm.csv
    ("04_GLAZING_SHUTTERS" 0 (
      (12979.2366 2187.0992) (12956.7481 2202.2443) (12931.2977 2217.1298) (12904.8702 2230.4122) (12877.5725 2242.0305)
      (12849.5115 2251.9542) (12820.8397 2260.1374) (12791.6489 2266.5344) (12762.0763 2271.1298) (12732.2443 2273.8931)
      (12702.2901 2274.8092) (12672.3359 2273.8931) (12642.5038 2271.1298) (12612.9313 2266.5344) (12583.7405 2260.1374)
      (12555.0687 2251.9542) (12527.0229 2242.0305) (12499.7099 2230.4122) (12473.2824 2217.1298) (12447.8321 2202.2443)
      (12425.3435 2187.0992)
    ))
    ; P1292 -- see feature_dimensions_mm.csv
    ("04_GLAZING_SHUTTERS" 0 (
      (13144.8702 1955.0229) (13144.7023 1955.7099) (13136.0 1982.6718) (13125.4351 2009.0382) (13113.0687 2034.7023)
      (13098.9466 2059.542) (13083.1145 2083.4656) (13065.6641 2106.3664) (13046.6412 2128.1527) (13026.1527 2148.7023)
      (13004.2748 2167.9695) (12995.6794 2174.5954)
    ))
    ; P1293 -- see feature_dimensions_mm.csv
    ("04_GLAZING_SHUTTERS" 0 (
      (13175.5725 1099.2366) (13175.5725 977.0992)
    ))
    ; P1294 -- see feature_dimensions_mm.csv
    ("04_GLAZING_SHUTTERS" 0 (
      (13175.5725 977.0992) (13175.5725 961.8321)
    ))
    ; P1295 -- see feature_dimensions_mm.csv
    ("04_GLAZING_SHUTTERS" 0 (
      (13175.5725 961.8321) (13175.5725 839.6947)
    ))
    ; P1296 -- see feature_dimensions_mm.csv
    ("04_GLAZING_SHUTTERS" 0 (
      (13175.5725 839.6947) (13175.5725 824.4275)
    ))
    ; P1297 -- see feature_dimensions_mm.csv
    ("04_GLAZING_SHUTTERS" 0 (
      (13175.5725 824.4275) (13175.5725 702.2901)
    ))
    ; P1298 -- see feature_dimensions_mm.csv
    ("04_GLAZING_SHUTTERS" 1 (
      (259.542 7450.3817) (854.9618 7450.3817) (854.9618 5893.1298) (259.542 5893.1298)
    ))
    ; P1299 -- see feature_dimensions_mm.csv
    ("04_GLAZING_SHUTTERS" 1 (
      (259.542 5770.9924) (854.9618 5770.9924) (854.9618 4213.7405) (259.542 4213.7405)
    ))
    ; P1300 -- see feature_dimensions_mm.csv
    ("04_GLAZING_SHUTTERS" 1 (
      (1236.6412 7435.1145) (1358.7786 7435.1145) (1358.7786 7145.0382) (1236.6412 7145.0382)
    ))
    ; P1301 -- see feature_dimensions_mm.csv
    ("04_GLAZING_SHUTTERS" 1 (
      (1725.1908 7435.1145) (1847.3282 7435.1145) (1847.3282 7145.0382) (1725.1908 7145.0382)
    ))
    ; P1302 -- see feature_dimensions_mm.csv
    ("04_GLAZING_SHUTTERS" 1 (
      (1969.4656 3068.7023) (2030.5344 3068.7023) (2030.5344 2839.6947) (1969.4656 2839.6947)
    ))
    ; P1303 -- see feature_dimensions_mm.csv
    ("04_GLAZING_SHUTTERS" 1 (
      (2198.4733 7435.1145) (2320.6107 7435.1145) (2320.6107 7145.0382) (2198.4733 7145.0382)
    ))
    ; P1304 -- see feature_dimensions_mm.csv
    ("04_GLAZING_SHUTTERS" 1 (
      (2259.542 3068.7023) (2320.6107 3068.7023) (2320.6107 2839.6947) (2259.542 2839.6947)
    ))
    ; P1305 -- see feature_dimensions_mm.csv
    ("04_GLAZING_SHUTTERS" 1 (
      (2549.6183 3068.7023) (2610.687 3068.7023) (2610.687 2839.6947) (2549.6183 2839.6947)
    ))
    ; P1306 -- see feature_dimensions_mm.csv
    ("04_GLAZING_SHUTTERS" 1 (
      (2687.0229 7435.1145) (2809.1603 7435.1145) (2809.1603 7145.0382) (2687.0229 7145.0382)
    ))
    ; P1307 -- see feature_dimensions_mm.csv
    ("04_GLAZING_SHUTTERS" 1 (
      (3160.3053 7435.1145) (3282.4427 7435.1145) (3282.4427 7145.0382) (3160.3053 7145.0382)
    ))
    ; P1308 -- see feature_dimensions_mm.csv
    ("04_GLAZING_SHUTTERS" 1 (
      (3374.0458 3068.7023) (3435.1145 3068.7023) (3435.1145 2839.6947) (3374.0458 2839.6947)
    ))
    ; P1309 -- see feature_dimensions_mm.csv
    ("04_GLAZING_SHUTTERS" 1 (
      (3648.855 7435.1145) (3770.9924 7435.1145) (3770.9924 7145.0382) (3648.855 7145.0382)
    ))
    ; P1310 -- see feature_dimensions_mm.csv
    ("04_GLAZING_SHUTTERS" 1 (
      (3664.1221 3068.7023) (3725.1908 3068.7023) (3725.1908 2839.6947) (3664.1221 2839.6947)
    ))
    ; P1311 -- see feature_dimensions_mm.csv
    ("04_GLAZING_SHUTTERS" 1 (
      (3954.1985 3068.7023) (4015.2672 3068.7023) (4015.2672 2839.6947) (3954.1985 2839.6947)
    ))
    ; P1312 -- see feature_dimensions_mm.csv
    ("04_GLAZING_SHUTTERS" 1 (
      (4122.1374 7435.1145) (4244.2748 7435.1145) (4244.2748 7145.0382) (4122.1374 7145.0382)
    ))
    ; P1313 -- see feature_dimensions_mm.csv
    ("04_GLAZING_SHUTTERS" 1 (
      (4610.687 7435.1145) (4732.8244 7435.1145) (4732.8244 7145.0382) (4610.687 7145.0382)
    ))
    ; P1314 -- see feature_dimensions_mm.csv
    ("04_GLAZING_SHUTTERS" 1 (
      (5450.3817 4503.8168) (5908.3969 4503.8168) (5908.3969 4432.0611) (5450.3817 4432.0611)
    ))
    ; P1315 -- see feature_dimensions_mm.csv
    ("04_GLAZING_SHUTTERS" 1 (
      (5450.3817 4400.0) (5908.3969 4400.0) (5908.3969 4328.2443) (5450.3817 4328.2443)
    ))
    ; P1316 -- see feature_dimensions_mm.csv
    ("04_GLAZING_SHUTTERS" 1 (
      (5450.3817 4296.1832) (5908.3969 4296.1832) (5908.3969 4224.4275) (5450.3817 4224.4275)
    ))
    ; P1317 -- see feature_dimensions_mm.csv
    ("04_GLAZING_SHUTTERS" 1 (
      (5450.3817 4192.3664) (5908.3969 4192.3664) (5908.3969 4120.6107) (5450.3817 4120.6107)
    ))
    ; P1318 -- see feature_dimensions_mm.csv
    ("04_GLAZING_SHUTTERS" 1 (
      (5450.3817 4088.5496) (5908.3969 4088.5496) (5908.3969 4016.7939) (5450.3817 4016.7939)
    ))
    ; P1319 -- see feature_dimensions_mm.csv
    ("04_GLAZING_SHUTTERS" 1 (
      (5450.3817 3984.7328) (5908.3969 3984.7328) (5908.3969 3912.9771) (5450.3817 3912.9771)
    ))
    ; P1320 -- see feature_dimensions_mm.csv
    ("04_GLAZING_SHUTTERS" 1 (
      (5450.3817 3880.916) (5908.3969 3880.916) (5908.3969 3809.1603) (5450.3817 3809.1603)
    ))
    ; P1321 -- see feature_dimensions_mm.csv
    ("04_GLAZING_SHUTTERS" 1 (
      (5450.3817 3777.0992) (5908.3969 3777.0992) (5908.3969 3705.3435) (5450.3817 3705.3435)
    ))
    ; P1322 -- see feature_dimensions_mm.csv
    ("04_GLAZING_SHUTTERS" 1 (
      (5450.3817 3673.2824) (5908.3969 3673.2824) (5908.3969 3601.5267) (5450.3817 3601.5267)
    ))
    ; P1323 -- see feature_dimensions_mm.csv
    ("04_GLAZING_SHUTTERS" 1 (
      (5450.3817 3569.4656) (5908.3969 3569.4656) (5908.3969 3497.7099) (5450.3817 3497.7099)
    ))
    ; P1324 -- see feature_dimensions_mm.csv
    ("04_GLAZING_SHUTTERS" 1 (
      (5450.3817 3465.6489) (5908.3969 3465.6489) (5908.3969 3393.8931) (5450.3817 3393.8931)
    ))
    ; P1325 -- see feature_dimensions_mm.csv
    ("04_GLAZING_SHUTTERS" 1 (
      (5450.3817 3361.8321) (5908.3969 3361.8321) (5908.3969 3290.0763) (5450.3817 3290.0763)
    ))
    ; P1326 -- see feature_dimensions_mm.csv
    ("04_GLAZING_SHUTTERS" 1 (
      (5450.3817 3258.0153) (5908.3969 3258.0153) (5908.3969 3186.2595) (5450.3817 3186.2595)
    ))
    ; P1327 -- see feature_dimensions_mm.csv
    ("04_GLAZING_SHUTTERS" 1 (
      (5450.3817 3154.1985) (5908.3969 3154.1985) (5908.3969 3082.4427) (5450.3817 3082.4427)
    ))
    ; P1328 -- see feature_dimensions_mm.csv
    ("04_GLAZING_SHUTTERS" 1 (
      (5450.3817 3050.3817) (5908.3969 3050.3817) (5908.3969 2978.626) (5450.3817 2978.626)
    ))
    ; P1329 -- see feature_dimensions_mm.csv
    ("04_GLAZING_SHUTTERS" 1 (
      (5450.3817 2946.5649) (5908.3969 2946.5649) (5908.3969 2874.8092) (5450.3817 2874.8092)
    ))
    ; P1330 -- see feature_dimensions_mm.csv
    ("04_GLAZING_SHUTTERS" 1 (
      (5450.3817 2842.7481) (5908.3969 2842.7481) (5908.3969 2770.9924) (5450.3817 2770.9924)
    ))
    ; P1331 -- see feature_dimensions_mm.csv
    ("04_GLAZING_SHUTTERS" 1 (
      (5450.3817 2738.9313) (5908.3969 2738.9313) (5908.3969 2667.1756) (5450.3817 2667.1756)
    ))
    ; P1332 -- see feature_dimensions_mm.csv
    ("04_GLAZING_SHUTTERS" 1 (
      (5450.3817 2635.1145) (5908.3969 2635.1145) (5908.3969 2563.3588) (5450.3817 2563.3588)
    ))
    ; P1333 -- see feature_dimensions_mm.csv
    ("04_GLAZING_SHUTTERS" 1 (
      (5450.3817 2531.2977) (5908.3969 2531.2977) (5908.3969 2459.542) (5450.3817 2459.542)
    ))
    ; P1334 -- see feature_dimensions_mm.csv
    ("04_GLAZING_SHUTTERS" 1 (
      (5450.3817 2335.8779) (5908.3969 2335.8779) (5908.3969 1251.9084) (5450.3817 1251.9084)
    ))
    ; P1335 -- see feature_dimensions_mm.csv
    ("04_GLAZING_SHUTTERS" 1 (
      (5526.7176 5328.2443) (5633.5878 5129.771) (5526.7176 4580.1527) (5832.0611 4580.1527) (5725.1908 5129.771)
      (5832.0611 5328.2443) (5679.3893 5526.7176)
    ))
    ; P1336 -- see feature_dimensions_mm.csv
    ("04_GLAZING_SHUTTERS" 1 (
      (5557.2519 2290.0763) (5557.2519 1877.8626) (5633.5878 1709.9237) (5557.2519 1480.916) (5557.2519 1282.4427)
      (5801.5267 1282.4427) (5801.5267 1480.916) (5725.1908 1709.9237) (5801.5267 1877.8626) (5801.5267 2290.0763)
    ))
    ; P1337 -- see feature_dimensions_mm.csv
    ("04_GLAZING_SHUTTERS" 1 (
      (6427.4809 4503.8168) (7312.9771 4503.8168) (7312.9771 4432.0611) (6427.4809 4432.0611)
    ))
    ; P1338 -- see feature_dimensions_mm.csv
    ("04_GLAZING_SHUTTERS" 1 (
      (6427.4809 4400.0) (7312.9771 4400.0) (7312.9771 4328.2443) (6427.4809 4328.2443)
    ))
    ; P1339 -- see feature_dimensions_mm.csv
    ("04_GLAZING_SHUTTERS" 1 (
      (6427.4809 4296.1832) (7312.9771 4296.1832) (7312.9771 4224.4275) (6427.4809 4224.4275)
    ))
    ; P1340 -- see feature_dimensions_mm.csv
    ("04_GLAZING_SHUTTERS" 1 (
      (6427.4809 4192.3664) (7312.9771 4192.3664) (7312.9771 4120.6107) (6427.4809 4120.6107)
    ))
    ; P1341 -- see feature_dimensions_mm.csv
    ("04_GLAZING_SHUTTERS" 1 (
      (6427.4809 4088.5496) (7312.9771 4088.5496) (7312.9771 4016.7939) (6427.4809 4016.7939)
    ))
    ; P1342 -- see feature_dimensions_mm.csv
    ("04_GLAZING_SHUTTERS" 1 (
      (6427.4809 3984.7328) (7312.9771 3984.7328) (7312.9771 3912.9771) (6427.4809 3912.9771)
    ))
    ; P1343 -- see feature_dimensions_mm.csv
    ("04_GLAZING_SHUTTERS" 1 (
      (6427.4809 3880.916) (7312.9771 3880.916) (7312.9771 3809.1603) (6427.4809 3809.1603)
    ))
    ; P1344 -- see feature_dimensions_mm.csv
    ("04_GLAZING_SHUTTERS" 1 (
      (6427.4809 3777.0992) (7312.9771 3777.0992) (7312.9771 3705.3435) (6427.4809 3705.3435)
    ))
    ; P1345 -- see feature_dimensions_mm.csv
    ("04_GLAZING_SHUTTERS" 1 (
      (6427.4809 3673.2824) (7312.9771 3673.2824) (7312.9771 3601.5267) (6427.4809 3601.5267)
    ))
    ; P1346 -- see feature_dimensions_mm.csv
    ("04_GLAZING_SHUTTERS" 1 (
      (6427.4809 3569.4656) (7312.9771 3569.4656) (7312.9771 3497.7099) (6427.4809 3497.7099)
    ))
    ; P1347 -- see feature_dimensions_mm.csv
    ("04_GLAZING_SHUTTERS" 1 (
      (6427.4809 3465.6489) (7312.9771 3465.6489) (7312.9771 3393.8931) (6427.4809 3393.8931)
    ))
    ; P1348 -- see feature_dimensions_mm.csv
    ("04_GLAZING_SHUTTERS" 1 (
      (6427.4809 3361.8321) (7312.9771 3361.8321) (7312.9771 3290.0763) (6427.4809 3290.0763)
    ))
    ; P1349 -- see feature_dimensions_mm.csv
    ("04_GLAZING_SHUTTERS" 1 (
      (6427.4809 3258.0153) (7312.9771 3258.0153) (7312.9771 3186.2595) (6427.4809 3186.2595)
    ))
    ; P1350 -- see feature_dimensions_mm.csv
    ("04_GLAZING_SHUTTERS" 1 (
      (6427.4809 3154.1985) (7312.9771 3154.1985) (7312.9771 3082.4427) (6427.4809 3082.4427)
    ))
    ; P1351 -- see feature_dimensions_mm.csv
    ("04_GLAZING_SHUTTERS" 1 (
      (6427.4809 3050.3817) (7312.9771 3050.3817) (7312.9771 2978.626) (6427.4809 2978.626)
    ))
    ; P1352 -- see feature_dimensions_mm.csv
    ("04_GLAZING_SHUTTERS" 1 (
      (6427.4809 2946.5649) (7312.9771 2946.5649) (7312.9771 2874.8092) (6427.4809 2874.8092)
    ))
    ; P1353 -- see feature_dimensions_mm.csv
    ("04_GLAZING_SHUTTERS" 1 (
      (6427.4809 2842.7481) (7312.9771 2842.7481) (7312.9771 2770.9924) (6427.4809 2770.9924)
    ))
    ; P1354 -- see feature_dimensions_mm.csv
    ("04_GLAZING_SHUTTERS" 1 (
      (6427.4809 2738.9313) (7312.9771 2738.9313) (7312.9771 2667.1756) (6427.4809 2667.1756)
    ))
    ; P1355 -- see feature_dimensions_mm.csv
    ("04_GLAZING_SHUTTERS" 1 (
      (6427.4809 2635.1145) (7312.9771 2635.1145) (7312.9771 2563.3588) (6427.4809 2563.3588)
    ))
    ; P1356 -- see feature_dimensions_mm.csv
    ("04_GLAZING_SHUTTERS" 1 (
      (6427.4809 2531.2977) (7312.9771 2531.2977) (7312.9771 2459.542) (6427.4809 2459.542)
    ))
    ; P1357 -- see feature_dimensions_mm.csv
    ("04_GLAZING_SHUTTERS" 1 (
      (6427.4809 2335.8779) (7312.9771 2335.8779) (7312.9771 1251.9084) (6427.4809 1251.9084)
    ))
    ; P1358 -- see feature_dimensions_mm.csv
    ("04_GLAZING_SHUTTERS" 1 (
      (6442.7481 5267.1756) (6442.7481 4549.6183) (6717.5573 4549.6183) (6824.4275 5007.6336)
    ))
    ; P1359 -- see feature_dimensions_mm.csv
    ("04_GLAZING_SHUTTERS" 1 (
      (6656.4885 5236.6412) (6870.229 5022.9008) (7083.9695 5236.6412) (6870.229 5511.4504)
    ))
    ; P1360 -- see feature_dimensions_mm.csv
    ("04_GLAZING_SHUTTERS" 1 (
      (6916.0305 5007.6336) (7022.9008 4549.6183) (7297.7099 4549.6183) (7297.7099 5267.1756)
    ))
    ; P1361 -- see feature_dimensions_mm.csv
    ("04_GLAZING_SHUTTERS" 1 (
      (7847.3282 4503.8168) (8290.0763 4503.8168) (8290.0763 4432.0611) (7847.3282 4432.0611)
    ))
    ; P1362 -- see feature_dimensions_mm.csv
    ("04_GLAZING_SHUTTERS" 1 (
      (7847.3282 4400.0) (8290.0763 4400.0) (8290.0763 4328.2443) (7847.3282 4328.2443)
    ))
    ; P1363 -- see feature_dimensions_mm.csv
    ("04_GLAZING_SHUTTERS" 1 (
      (7847.3282 4296.1832) (8290.0763 4296.1832) (8290.0763 4224.4275) (7847.3282 4224.4275)
    ))
    ; P1364 -- see feature_dimensions_mm.csv
    ("04_GLAZING_SHUTTERS" 1 (
      (7847.3282 4192.3664) (8290.0763 4192.3664) (8290.0763 4120.6107) (7847.3282 4120.6107)
    ))
    ; P1365 -- see feature_dimensions_mm.csv
    ("04_GLAZING_SHUTTERS" 1 (
      (7847.3282 4088.5496) (8290.0763 4088.5496) (8290.0763 4016.7939) (7847.3282 4016.7939)
    ))
    ; P1366 -- see feature_dimensions_mm.csv
    ("04_GLAZING_SHUTTERS" 1 (
      (7847.3282 3984.7328) (8290.0763 3984.7328) (8290.0763 3912.9771) (7847.3282 3912.9771)
    ))
    ; P1367 -- see feature_dimensions_mm.csv
    ("04_GLAZING_SHUTTERS" 1 (
      (7847.3282 3880.916) (8290.0763 3880.916) (8290.0763 3809.1603) (7847.3282 3809.1603)
    ))
    ; P1368 -- see feature_dimensions_mm.csv
    ("04_GLAZING_SHUTTERS" 1 (
      (7847.3282 3777.0992) (8290.0763 3777.0992) (8290.0763 3705.3435) (7847.3282 3705.3435)
    ))
    ; P1369 -- see feature_dimensions_mm.csv
    ("04_GLAZING_SHUTTERS" 1 (
      (7847.3282 3673.2824) (8290.0763 3673.2824) (8290.0763 3601.5267) (7847.3282 3601.5267)
    ))
    ; P1370 -- see feature_dimensions_mm.csv
    ("04_GLAZING_SHUTTERS" 1 (
      (7847.3282 3569.4656) (8290.0763 3569.4656) (8290.0763 3497.7099) (7847.3282 3497.7099)
    ))
    ; P1371 -- see feature_dimensions_mm.csv
    ("04_GLAZING_SHUTTERS" 1 (
      (7847.3282 3465.6489) (8290.0763 3465.6489) (8290.0763 3393.8931) (7847.3282 3393.8931)
    ))
    ; P1372 -- see feature_dimensions_mm.csv
    ("04_GLAZING_SHUTTERS" 1 (
      (7847.3282 3361.8321) (8290.0763 3361.8321) (8290.0763 3290.0763) (7847.3282 3290.0763)
    ))
    ; P1373 -- see feature_dimensions_mm.csv
    ("04_GLAZING_SHUTTERS" 1 (
      (7847.3282 3258.0153) (8290.0763 3258.0153) (8290.0763 3186.2595) (7847.3282 3186.2595)
    ))
    ; P1374 -- see feature_dimensions_mm.csv
    ("04_GLAZING_SHUTTERS" 1 (
      (7847.3282 3154.1985) (8290.0763 3154.1985) (8290.0763 3082.4427) (7847.3282 3082.4427)
    ))
    ; P1375 -- see feature_dimensions_mm.csv
    ("04_GLAZING_SHUTTERS" 1 (
      (7847.3282 3050.3817) (8290.0763 3050.3817) (8290.0763 2978.626) (7847.3282 2978.626)
    ))
    ; P1376 -- see feature_dimensions_mm.csv
    ("04_GLAZING_SHUTTERS" 1 (
      (7847.3282 2946.5649) (8290.0763 2946.5649) (8290.0763 2874.8092) (7847.3282 2874.8092)
    ))
    ; P1377 -- see feature_dimensions_mm.csv
    ("04_GLAZING_SHUTTERS" 1 (
      (7847.3282 2842.7481) (8290.0763 2842.7481) (8290.0763 2770.9924) (7847.3282 2770.9924)
    ))
    ; P1378 -- see feature_dimensions_mm.csv
    ("04_GLAZING_SHUTTERS" 1 (
      (7847.3282 2738.9313) (8290.0763 2738.9313) (8290.0763 2667.1756) (7847.3282 2667.1756)
    ))
    ; P1379 -- see feature_dimensions_mm.csv
    ("04_GLAZING_SHUTTERS" 1 (
      (7847.3282 2635.1145) (8290.0763 2635.1145) (8290.0763 2563.3588) (7847.3282 2563.3588)
    ))
    ; P1380 -- see feature_dimensions_mm.csv
    ("04_GLAZING_SHUTTERS" 1 (
      (7847.3282 2531.2977) (8290.0763 2531.2977) (8290.0763 2459.542) (7847.3282 2459.542)
    ))
    ; P1381 -- see feature_dimensions_mm.csv
    ("04_GLAZING_SHUTTERS" 1 (
      (7847.3282 2335.8779) (8290.0763 2335.8779) (8290.0763 1251.9084) (7847.3282 1251.9084)
    ))
    ; P1382 -- see feature_dimensions_mm.csv
    ("04_GLAZING_SHUTTERS" 1 (
      (7916.0305 5328.2443) (8022.9008 5129.771) (7916.0305 4580.1527) (8221.374 4580.1527) (8114.5038 5129.771)
      (8221.374 5328.2443) (8068.7023 5526.7176)
    ))
    ; P1383 -- see feature_dimensions_mm.csv
    ("04_GLAZING_SHUTTERS" 1 (
      (7946.5649 2290.0763) (7946.5649 1877.8626) (8022.9008 1709.9237) (7946.5649 1480.916) (7946.5649 1282.4427)
      (8190.8397 1282.4427) (8190.8397 1480.916) (8114.5038 1709.9237) (8190.8397 1877.8626) (8190.8397 2290.0763)
    ))
    ; P1384 -- see feature_dimensions_mm.csv
    ("04_GLAZING_SHUTTERS" 1 (
      (9022.9008 7450.3817) (9022.9008 7145.0382) (9145.0382 7145.0382) (9145.0382 7450.3817)
    ))
    ; P1385 -- see feature_dimensions_mm.csv
    ("04_GLAZING_SHUTTERS" 1 (
      (9435.1145 7450.3817) (9435.1145 7145.0382) (9557.2519 7145.0382) (9557.2519 7450.3817)
    ))
    ; P1386 -- see feature_dimensions_mm.csv
    ("04_GLAZING_SHUTTERS" 1 (
      (9847.3282 7450.3817) (9847.3282 7145.0382) (9969.4656 7145.0382) (9969.4656 7450.3817)
    ))
    ; P1387 -- see feature_dimensions_mm.csv
    ("04_GLAZING_SHUTTERS" 1 (
      (10549.6183 7435.1145) (10671.7557 7435.1145) (10671.7557 7145.0382) (10549.6183 7145.0382)
    ))
    ; P1388 -- see feature_dimensions_mm.csv
    ("04_GLAZING_SHUTTERS" 1 (
      (11038.1679 7435.1145) (11160.3053 7435.1145) (11160.3053 7145.0382) (11038.1679 7145.0382)
    ))
    ; P1389 -- see feature_dimensions_mm.csv
    ("04_GLAZING_SHUTTERS" 1 (
      (11068.7023 3068.7023) (11129.771 3068.7023) (11129.771 2839.6947) (11068.7023 2839.6947)
    ))
    ; P1390 -- see feature_dimensions_mm.csv
    ("04_GLAZING_SHUTTERS" 1 (
      (11343.5115 3068.7023) (11404.5802 3068.7023) (11404.5802 2839.6947) (11343.5115 2839.6947)
    ))
    ; P1391 -- see feature_dimensions_mm.csv
    ("04_GLAZING_SHUTTERS" 1 (
      (11526.7176 7435.1145) (11648.855 7435.1145) (11648.855 7145.0382) (11526.7176 7145.0382)
    ))
    ; P1392 -- see feature_dimensions_mm.csv
    ("04_GLAZING_SHUTTERS" 1 (
      (11633.5878 3068.7023) (11694.6565 3068.7023) (11694.6565 2839.6947) (11633.5878 2839.6947)
    ))
    ; P1393 -- see feature_dimensions_mm.csv
    ("04_GLAZING_SHUTTERS" 1 (
      (12015.2672 7435.1145) (12137.4046 7435.1145) (12137.4046 7145.0382) (12015.2672 7145.0382)
    ))
    ; P1394 -- see feature_dimensions_mm.csv
    ("04_GLAZING_SHUTTERS" 1 (
      (12442.7481 3068.7023) (12503.8168 3068.7023) (12503.8168 2839.6947) (12442.7481 2839.6947)
    ))
    ; P1395 -- see feature_dimensions_mm.csv
    ("04_GLAZING_SHUTTERS" 1 (
      (12503.8168 7435.1145) (12625.9542 7435.1145) (12625.9542 7145.0382) (12503.8168 7145.0382)
    ))
    ; P1396 -- see feature_dimensions_mm.csv
    ("04_GLAZING_SHUTTERS" 1 (
      (12732.8244 3068.7023) (12793.8931 3068.7023) (12793.8931 2839.6947) (12732.8244 2839.6947)
    ))
    ; P1397 -- see feature_dimensions_mm.csv
    ("04_GLAZING_SHUTTERS" 1 (
      (12992.3664 7435.1145) (13114.5038 7435.1145) (13114.5038 7145.0382) (12992.3664 7145.0382)
    ))
    ; P1398 -- see feature_dimensions_mm.csv
    ("04_GLAZING_SHUTTERS" 1 (
      (13022.9008 3068.7023) (13083.9695 3068.7023) (13083.9695 2839.6947) (13022.9008 2839.6947)
    ))
    ; P1399 -- see feature_dimensions_mm.csv
    ("04_GLAZING_SHUTTERS" 1 (
      (13465.6489 7435.1145) (13587.7863 7435.1145) (13587.7863 7145.0382) (13465.6489 7145.0382)
    ))
    ; P1400 -- see feature_dimensions_mm.csv
    ("05_STONE_JOINTS" 0 (
      (183.2061 9236.6412) (503.8168 9236.6412)
    ))
    ; P1401 -- see feature_dimensions_mm.csv
    ("05_STONE_JOINTS" 0 (
      (183.2061 9236.6412) (183.2061 9160.3053)
    ))
    ; P1402 -- see feature_dimensions_mm.csv
    ("05_STONE_JOINTS" 0 (
      (503.8168 9572.5191) (183.2061 9572.5191) (183.2061 9557.2519) (183.2061 9236.6412)
    ))
    ; P1403 -- see feature_dimensions_mm.csv
    ("05_STONE_JOINTS" 0 (
      (183.2061 9160.3053) (519.084 9160.3053)
    ))
    ; P1404 -- see feature_dimensions_mm.csv
    ("05_STONE_JOINTS" 0 (
      (183.2061 9160.3053) (183.2061 9083.9695)
    ))
    ; P1405 -- see feature_dimensions_mm.csv
    ("05_STONE_JOINTS" 0 (
      (183.2061 9083.9695) (519.084 9083.9695)
    ))
    ; P1406 -- see feature_dimensions_mm.csv
    ("05_STONE_JOINTS" 0 (
      (183.2061 9083.9695) (183.2061 8992.3664)
    ))
    ; P1407 -- see feature_dimensions_mm.csv
    ("05_STONE_JOINTS" 0 (
      (183.2061 8992.3664) (519.084 8992.3664)
    ))
    ; P1408 -- see feature_dimensions_mm.csv
    ("05_STONE_JOINTS" 0 (
      (183.2061 8992.3664) (183.2061 8900.7634)
    ))
    ; P1409 -- see feature_dimensions_mm.csv
    ("05_STONE_JOINTS" 0 (
      (183.2061 8900.7634) (503.8168 8900.7634)
    ))
    ; P1410 -- see feature_dimensions_mm.csv
    ("05_STONE_JOINTS" 0 (
      (183.2061 8900.7634) (183.2061 8564.8855)
    ))
    ; P1411 -- see feature_dimensions_mm.csv
    ("05_STONE_JOINTS" 0 (
      (183.2061 8564.8855) (503.8168 8564.8855)
    ))
    ; P1412 -- see feature_dimensions_mm.csv
    ("05_STONE_JOINTS" 0 (
      (183.2061 8564.8855) (183.2061 8488.5496)
    ))
    ; P1413 -- see feature_dimensions_mm.csv
    ("05_STONE_JOINTS" 0 (
      (183.2061 8488.5496) (519.084 8488.5496)
    ))
    ; P1414 -- see feature_dimensions_mm.csv
    ("05_STONE_JOINTS" 0 (
      (183.2061 8488.5496) (183.2061 8412.2137)
    ))
    ; P1415 -- see feature_dimensions_mm.csv
    ("05_STONE_JOINTS" 0 (
      (183.2061 8412.2137) (519.084 8412.2137)
    ))
    ; P1416 -- see feature_dimensions_mm.csv
    ("05_STONE_JOINTS" 0 (
      (183.2061 8412.2137) (183.2061 8320.6107)
    ))
    ; P1417 -- see feature_dimensions_mm.csv
    ("05_STONE_JOINTS" 0 (
      (183.2061 8320.6107) (519.084 8320.6107)
    ))
    ; P1418 -- see feature_dimensions_mm.csv
    ("05_STONE_JOINTS" 0 (
      (183.2061 8320.6107) (183.2061 8229.0076)
    ))
    ; P1419 -- see feature_dimensions_mm.csv
    ("05_STONE_JOINTS" 0 (
      (183.2061 8229.0076) (503.8168 8229.0076)
    ))
    ; P1420 -- see feature_dimensions_mm.csv
    ("05_STONE_JOINTS" 0 (
      (183.2061 8229.0076) (183.2061 7893.1298)
    ))
    ; P1421 -- see feature_dimensions_mm.csv
    ("05_STONE_JOINTS" 0 (
      (183.2061 7893.1298) (503.8168 7893.1298)
    ))
    ; P1422 -- see feature_dimensions_mm.csv
    ("05_STONE_JOINTS" 0 (
      (183.2061 7893.1298) (183.2061 7816.7939)
    ))
    ; P1423 -- see feature_dimensions_mm.csv
    ("05_STONE_JOINTS" 0 (
      (183.2061 7816.7939) (519.084 7816.7939)
    ))
    ; P1424 -- see feature_dimensions_mm.csv
    ("05_STONE_JOINTS" 0 (
      (183.2061 7816.7939) (183.2061 7740.458)
    ))
    ; P1425 -- see feature_dimensions_mm.csv
    ("05_STONE_JOINTS" 0 (
      (183.2061 7740.458) (519.084 7740.458)
    ))
    ; P1426 -- see feature_dimensions_mm.csv
    ("05_STONE_JOINTS" 0 (
      (183.2061 7740.458) (183.2061 7648.855)
    ))
    ; P1427 -- see feature_dimensions_mm.csv
    ("05_STONE_JOINTS" 0 (
      (183.2061 7648.855) (519.084 7648.855)
    ))
    ; P1428 -- see feature_dimensions_mm.csv
    ("05_STONE_JOINTS" 0 (
      (183.2061 7648.855) (183.2061 7557.2519)
    ))
    ; P1429 -- see feature_dimensions_mm.csv
    ("05_STONE_JOINTS" 0 (
      (183.2061 7557.2519) (503.8168 7557.2519)
    ))
    ; P1430 -- see feature_dimensions_mm.csv
    ("05_STONE_JOINTS" 0 (
      (183.2061 7557.2519) (183.2061 7221.374)
    ))
    ; P1431 -- see feature_dimensions_mm.csv
    ("05_STONE_JOINTS" 0 (
      (183.2061 7221.374) (213.7405 7221.374)
    ))
    ; P1432 -- see feature_dimensions_mm.csv
    ("05_STONE_JOINTS" 0 (
      (183.2061 7221.374) (183.2061 7145.0382)
    ))
    ; P1433 -- see feature_dimensions_mm.csv
    ("05_STONE_JOINTS" 0 (
      (183.2061 7145.0382) (213.7405 7145.0382)
    ))
    ; P1434 -- see feature_dimensions_mm.csv
    ("05_STONE_JOINTS" 0 (
      (183.2061 7145.0382) (183.2061 7068.7023)
    ))
    ; P1435 -- see feature_dimensions_mm.csv
    ("05_STONE_JOINTS" 0 (
      (183.2061 7068.7023) (213.7405 7068.7023)
    ))
    ; P1436 -- see feature_dimensions_mm.csv
    ("05_STONE_JOINTS" 0 (
      (183.2061 7068.7023) (183.2061 6977.0992)
    ))
    ; P1437 -- see feature_dimensions_mm.csv
    ("05_STONE_JOINTS" 0 (
      (183.2061 6977.0992) (213.7405 6977.0992)
    ))
    ; P1438 -- see feature_dimensions_mm.csv
    ("05_STONE_JOINTS" 0 (
      (183.2061 6977.0992) (183.2061 6885.4962)
    ))
    ; P1439 -- see feature_dimensions_mm.csv
    ("05_STONE_JOINTS" 0 (
      (183.2061 6885.4962) (213.7405 6885.4962)
    ))
    ; P1440 -- see feature_dimensions_mm.csv
    ("05_STONE_JOINTS" 0 (
      (183.2061 6885.4962) (183.2061 6549.6183)
    ))
    ; P1441 -- see feature_dimensions_mm.csv
    ("05_STONE_JOINTS" 0 (
      (183.2061 6549.6183) (213.7405 6549.6183)
    ))
    ; P1442 -- see feature_dimensions_mm.csv
    ("05_STONE_JOINTS" 0 (
      (183.2061 6549.6183) (183.2061 6473.2824)
    ))
    ; P1443 -- see feature_dimensions_mm.csv
    ("05_STONE_JOINTS" 0 (
      (183.2061 6473.2824) (213.7405 6473.2824)
    ))
    ; P1444 -- see feature_dimensions_mm.csv
    ("05_STONE_JOINTS" 0 (
      (183.2061 6473.2824) (183.2061 6396.9466)
    ))
    ; P1445 -- see feature_dimensions_mm.csv
    ("05_STONE_JOINTS" 0 (
      (183.2061 6396.9466) (213.7405 6396.9466)
    ))
    ; P1446 -- see feature_dimensions_mm.csv
    ("05_STONE_JOINTS" 0 (
      (183.2061 6396.9466) (183.2061 6305.3435)
    ))
    ; P1447 -- see feature_dimensions_mm.csv
    ("05_STONE_JOINTS" 0 (
      (183.2061 6305.3435) (213.7405 6305.3435)
    ))
    ; P1448 -- see feature_dimensions_mm.csv
    ("05_STONE_JOINTS" 0 (
      (183.2061 6305.3435) (183.2061 6213.7405)
    ))
    ; P1449 -- see feature_dimensions_mm.csv
    ("05_STONE_JOINTS" 0 (
      (183.2061 6213.7405) (213.7405 6213.7405)
    ))
    ; P1450 -- see feature_dimensions_mm.csv
    ("05_STONE_JOINTS" 0 (
      (183.2061 6213.7405) (183.2061 5877.8626)
    ))
    ; P1451 -- see feature_dimensions_mm.csv
    ("05_STONE_JOINTS" 0 (
      (183.2061 5877.8626) (213.7405 5877.8626)
    ))
    ; P1452 -- see feature_dimensions_mm.csv
    ("05_STONE_JOINTS" 0 (
      (183.2061 5877.8626) (183.2061 5801.5267) (213.7405 5801.5267)
    ))
    ; P1453 -- see feature_dimensions_mm.csv
    ("05_STONE_JOINTS" 0 (
      (183.2061 5633.5878) (213.7405 5633.5878)
    ))
    ; P1454 -- see feature_dimensions_mm.csv
    ("05_STONE_JOINTS" 0 (
      (183.2061 5633.5878) (183.2061 5541.9847) (213.7405 5541.9847)
    ))
    ; P1455 -- see feature_dimensions_mm.csv
    ("05_STONE_JOINTS" 0 (
      (183.2061 5633.5878) (183.2061 5725.1908) (213.7405 5725.1908)
    ))
    ; P1456 -- see feature_dimensions_mm.csv
    ("05_STONE_JOINTS" 0 (
      (183.2061 5206.1069) (213.7405 5206.1069)
    ))
    ; P1457 -- see feature_dimensions_mm.csv
    ("05_STONE_JOINTS" 0 (
      (183.2061 5129.771) (213.7405 5129.771)
    ))
    ; P1458 -- see feature_dimensions_mm.csv
    ("05_STONE_JOINTS" 0 (
      (183.2061 5053.4351) (213.7405 5053.4351)
    ))
    ; P1459 -- see feature_dimensions_mm.csv
    ("05_STONE_JOINTS" 0 (
      (183.2061 4961.8321) (213.7405 4961.8321) (213.7405 5053.4351)
    ))
    ; P1460 -- see feature_dimensions_mm.csv
    ("05_STONE_JOINTS" 0 (
      (183.2061 4870.229) (213.7405 4870.229)
    ))
    ; P1461 -- see feature_dimensions_mm.csv
    ("05_STONE_JOINTS" 0 (
      (183.2061 4534.3511) (213.7405 4534.3511)
    ))
    ; P1462 -- see feature_dimensions_mm.csv
    ("05_STONE_JOINTS" 0 (
      (183.2061 4458.0153) (213.7405 4458.0153)
    ))
    ; P1463 -- see feature_dimensions_mm.csv
    ("05_STONE_JOINTS" 0 (
      (183.2061 4381.6794) (213.7405 4381.6794)
    ))
    ; P1464 -- see feature_dimensions_mm.csv
    ("05_STONE_JOINTS" 0 (
      (183.2061 4290.0763) (213.7405 4290.0763)
    ))
    ; P1465 -- see feature_dimensions_mm.csv
    ("05_STONE_JOINTS" 0 (
      (183.2061 4198.4733) (213.7405 4198.4733)
    ))
    ; P1466 -- see feature_dimensions_mm.csv
    ("05_STONE_JOINTS" 0 (
      (183.2061 3862.5954) (503.8168 3862.5954)
    ))
    ; P1467 -- see feature_dimensions_mm.csv
    ("05_STONE_JOINTS" 0 (
      (183.2061 3709.9237) (519.084 3709.9237)
    ))
    ; P1468 -- see feature_dimensions_mm.csv
    ("05_STONE_JOINTS" 0 (
      (183.2061 3709.9237) (183.2061 3618.3206)
    ))
    ; P1469 -- see feature_dimensions_mm.csv
    ("05_STONE_JOINTS" 0 (
      (183.2061 3709.9237) (183.2061 3786.2595) (519.084 3786.2595)
    ))
    ; P1470 -- see feature_dimensions_mm.csv
    ("05_STONE_JOINTS" 0 (
      (183.2061 3618.3206) (519.084 3618.3206)
    ))
    ; P1471 -- see feature_dimensions_mm.csv
    ("05_STONE_JOINTS" 0 (
      (183.2061 3618.3206) (183.2061 3526.7176)
    ))
    ; P1472 -- see feature_dimensions_mm.csv
    ("05_STONE_JOINTS" 0 (
      (183.2061 3526.7176) (503.8168 3526.7176)
    ))
    ; P1473 -- see feature_dimensions_mm.csv
    ("05_STONE_JOINTS" 0 (
      (183.2061 3526.7176) (183.2061 3190.8397)
    ))
    ; P1474 -- see feature_dimensions_mm.csv
    ("05_STONE_JOINTS" 0 (
      (183.2061 3190.8397) (503.8168 3190.8397)
    ))
    ; P1475 -- see feature_dimensions_mm.csv
    ("05_STONE_JOINTS" 0 (
      (183.2061 3190.8397) (183.2061 3114.5038)
    ))
    ; P1476 -- see feature_dimensions_mm.csv
    ("05_STONE_JOINTS" 0 (
      (183.2061 3114.5038) (519.084 3114.5038)
    ))
    ; P1477 -- see feature_dimensions_mm.csv
    ("05_STONE_JOINTS" 0 (
      (183.2061 3114.5038) (183.2061 3038.1679)
    ))
    ; P1478 -- see feature_dimensions_mm.csv
    ("05_STONE_JOINTS" 0 (
      (183.2061 3038.1679) (519.084 3038.1679)
    ))
    ; P1479 -- see feature_dimensions_mm.csv
    ("05_STONE_JOINTS" 0 (
      (183.2061 3038.1679) (183.2061 2946.5649) (519.084 2946.5649)
    ))
    ; P1480 -- see feature_dimensions_mm.csv
    ("05_STONE_JOINTS" 0 (
      (183.2061 2854.9618) (503.8168 2854.9618)
    ))
    ; P1481 -- see feature_dimensions_mm.csv
    ("05_STONE_JOINTS" 0 (
      (183.2061 2519.084) (503.8168 2519.084)
    ))
    ; P1482 -- see feature_dimensions_mm.csv
    ("05_STONE_JOINTS" 0 (
      (183.2061 2442.7481) (519.084 2442.7481)
    ))
    ; P1483 -- see feature_dimensions_mm.csv
    ("05_STONE_JOINTS" 0 (
      (183.2061 2366.4122) (519.084 2366.4122)
    ))
    ; P1484 -- see feature_dimensions_mm.csv
    ("05_STONE_JOINTS" 0 (
      (183.2061 2274.8092) (519.084 2274.8092)
    ))
    ; P1485 -- see feature_dimensions_mm.csv
    ("05_STONE_JOINTS" 0 (
      (183.2061 2183.2061) (503.8168 2183.2061)
    ))
    ; P1486 -- see feature_dimensions_mm.csv
    ("05_STONE_JOINTS" 0 (
      (183.2061 1847.3282) (503.8168 1847.3282)
    ))
    ; P1487 -- see feature_dimensions_mm.csv
    ("05_STONE_JOINTS" 0 (
      (183.2061 1511.4504) (503.8168 1511.4504)
    ))
    ; P1488 -- see feature_dimensions_mm.csv
    ("05_STONE_JOINTS" 0 (
      (183.2061 1511.4504) (183.2061 1175.5725)
    ))
    ; P1489 -- see feature_dimensions_mm.csv
    ("05_STONE_JOINTS" 0 (
      (183.2061 1511.4504) (183.2061 1603.0534) (519.084 1603.0534)
    ))
    ; P1490 -- see feature_dimensions_mm.csv
    ("05_STONE_JOINTS" 0 (
      (183.2061 1175.5725) (503.8168 1175.5725)
    ))
    ; P1491 -- see feature_dimensions_mm.csv
    ("05_STONE_JOINTS" 0 (
      (183.2061 1175.5725) (183.2061 1099.2366)
    ))
    ; P1492 -- see feature_dimensions_mm.csv
    ("05_STONE_JOINTS" 0 (
      (183.2061 1099.2366) (519.084 1099.2366)
    ))
    ; P1493 -- see feature_dimensions_mm.csv
    ("05_STONE_JOINTS" 0 (
      (183.2061 1099.2366) (183.2061 1022.9008)
    ))
    ; P1494 -- see feature_dimensions_mm.csv
    ("05_STONE_JOINTS" 0 (
      (183.2061 1022.9008) (519.084 1022.9008)
    ))
    ; P1495 -- see feature_dimensions_mm.csv
    ("05_STONE_JOINTS" 0 (
      (183.2061 1022.9008) (183.2061 931.2977)
    ))
    ; P1496 -- see feature_dimensions_mm.csv
    ("05_STONE_JOINTS" 0 (
      (183.2061 931.2977) (519.084 931.2977)
    ))
    ; P1497 -- see feature_dimensions_mm.csv
    ("05_STONE_JOINTS" 0 (
      (183.2061 931.2977) (183.2061 839.6947)
    ))
    ; P1498 -- see feature_dimensions_mm.csv
    ("05_STONE_JOINTS" 0 (
      (183.2061 839.6947) (503.8168 839.6947)
    ))
    ; P1499 -- see feature_dimensions_mm.csv
    ("05_STONE_JOINTS" 0 (
      (183.2061 839.6947) (183.2061 809.1603) (503.8168 809.1603)
    ))
    ; P1500 -- see feature_dimensions_mm.csv
    ("05_STONE_JOINTS" 0 (
      (213.7405 7145.0382) (213.7405 7221.374)
    ))
    ; P1501 -- see feature_dimensions_mm.csv
    ("05_STONE_JOINTS" 0 (
      (213.7405 7221.374) (213.7405 7496.1832) (503.8168 7496.1832)
    ))
    ; P1502 -- see feature_dimensions_mm.csv
    ("05_STONE_JOINTS" 0 (
      (213.7405 7068.7023) (213.7405 7145.0382)
    ))
    ; P1503 -- see feature_dimensions_mm.csv
    ("05_STONE_JOINTS" 0 (
      (213.7405 6977.0992) (213.7405 7068.7023)
    ))
    ; P1504 -- see feature_dimensions_mm.csv
    ("05_STONE_JOINTS" 0 (
      (213.7405 6885.4962) (213.7405 6977.0992)
    ))
    ; P1505 -- see feature_dimensions_mm.csv
    ("05_STONE_JOINTS" 0 (
      (213.7405 6549.6183) (213.7405 6885.4962)
    ))
    ; P1506 -- see feature_dimensions_mm.csv
    ("05_STONE_JOINTS" 0 (
      (213.7405 6473.2824) (213.7405 6549.6183)
    ))
    ; P1507 -- see feature_dimensions_mm.csv
    ("05_STONE_JOINTS" 0 (
      (213.7405 6396.9466) (213.7405 6473.2824)
    ))
    ; P1508 -- see feature_dimensions_mm.csv
    ("05_STONE_JOINTS" 0 (
      (213.7405 6305.3435) (213.7405 6396.9466)
    ))
    ; P1509 -- see feature_dimensions_mm.csv
    ("05_STONE_JOINTS" 0 (
      (213.7405 6213.7405) (213.7405 6305.3435)
    ))
    ; P1510 -- see feature_dimensions_mm.csv
    ("05_STONE_JOINTS" 0 (
      (213.7405 5877.8626) (213.7405 6213.7405)
    ))
    ; P1511 -- see feature_dimensions_mm.csv
    ("05_STONE_JOINTS" 0 (
      (519.084 5847.3282) (213.7405 5847.3282) (213.7405 5877.8626)
    ))
    ; P1512 -- see feature_dimensions_mm.csv
    ("05_STONE_JOINTS" 0 (
      (213.7405 5725.1908) (213.7405 5801.5267)
    ))
    ; P1513 -- see feature_dimensions_mm.csv
    ("05_STONE_JOINTS" 0 (
      (213.7405 5801.5267) (213.7405 5816.7939) (519.084 5816.7939)
    ))
    ; P1514 -- see feature_dimensions_mm.csv
    ("05_STONE_JOINTS" 0 (
      (213.7405 5633.5878) (213.7405 5725.1908)
    ))
    ; P1515 -- see feature_dimensions_mm.csv
    ("05_STONE_JOINTS" 0 (
      (213.7405 5541.9847) (213.7405 5633.5878)
    ))
    ; P1516 -- see feature_dimensions_mm.csv
    ("05_STONE_JOINTS" 0 (
      (213.7405 5206.1069) (213.7405 5541.9847)
    ))
    ; P1517 -- see feature_dimensions_mm.csv
    ("05_STONE_JOINTS" 0 (
      (213.7405 5129.771) (213.7405 5206.1069)
    ))
    ; P1518 -- see feature_dimensions_mm.csv
    ("05_STONE_JOINTS" 0 (
      (213.7405 5053.4351) (213.7405 5129.771)
    ))
    ; P1519 -- see feature_dimensions_mm.csv
    ("05_STONE_JOINTS" 0 (
      (854.9618 9572.5191) (503.8168 9572.5191)
    ))
    ; P1520 -- see feature_dimensions_mm.csv
    ("05_STONE_JOINTS" 0 (
      (503.8168 9496.1832) (503.8168 9557.2519) (503.8168 9572.5191)
    ))
    ; P1521 -- see feature_dimensions_mm.csv
    ("05_STONE_JOINTS" 0 (
      (503.8168 9496.1832) (854.9618 9496.1832)
    ))
    ; P1522 -- see feature_dimensions_mm.csv
    ("05_STONE_JOINTS" 0 (
      (503.8168 9419.8473) (503.8168 9496.1832)
    ))
    ; P1523 -- see feature_dimensions_mm.csv
    ("05_STONE_JOINTS" 0 (
      (503.8168 9419.8473) (854.9618 9419.8473)
    ))
    ; P1524 -- see feature_dimensions_mm.csv
    ("05_STONE_JOINTS" 0 (
      (503.8168 9328.2443) (503.8168 9419.8473)
    ))
    ; P1525 -- see feature_dimensions_mm.csv
    ("05_STONE_JOINTS" 0 (
      (503.8168 9328.2443) (854.9618 9328.2443)
    ))
    ; P1526 -- see feature_dimensions_mm.csv
    ("05_STONE_JOINTS" 0 (
      (503.8168 9236.6412) (503.8168 9328.2443)
    ))
    ; P1527 -- see feature_dimensions_mm.csv
    ("05_STONE_JOINTS" 0 (
      (503.8168 9236.6412) (519.084 9236.6412)
    ))
    ; P1528 -- see feature_dimensions_mm.csv
    ("05_STONE_JOINTS" 0 (
      (503.8168 8900.7634) (519.084 8900.7634)
    ))
    ; P1529 -- see feature_dimensions_mm.csv
    ("05_STONE_JOINTS" 0 (
      (503.8168 8824.4275) (503.8168 8900.7634)
    ))
    ; P1530 -- see feature_dimensions_mm.csv
    ("05_STONE_JOINTS" 0 (
      (503.8168 8824.4275) (854.9618 8824.4275)
    ))
    ; P1531 -- see feature_dimensions_mm.csv
    ("05_STONE_JOINTS" 0 (
      (503.8168 8748.0916) (503.8168 8824.4275)
    ))
    ; P1532 -- see feature_dimensions_mm.csv
    ("05_STONE_JOINTS" 0 (
      (503.8168 8748.0916) (854.9618 8748.0916)
    ))
    ; P1533 -- see feature_dimensions_mm.csv
    ("05_STONE_JOINTS" 0 (
      (503.8168 8656.4885) (503.8168 8748.0916)
    ))
    ; P1534 -- see feature_dimensions_mm.csv
    ("05_STONE_JOINTS" 0 (
      (503.8168 8656.4885) (854.9618 8656.4885)
    ))
    ; P1535 -- see feature_dimensions_mm.csv
    ("05_STONE_JOINTS" 0 (
      (503.8168 8564.8855) (503.8168 8656.4885)
    ))
    ; P1536 -- see feature_dimensions_mm.csv
    ("05_STONE_JOINTS" 0 (
      (503.8168 8564.8855) (519.084 8564.8855)
    ))
    ; P1537 -- see feature_dimensions_mm.csv
    ("05_STONE_JOINTS" 0 (
      (503.8168 8229.0076) (519.084 8229.0076)
    ))
    ; P1538 -- see feature_dimensions_mm.csv
    ("05_STONE_JOINTS" 0 (
      (503.8168 8152.6718) (503.8168 8229.0076)
    ))
    ; P1539 -- see feature_dimensions_mm.csv
    ("05_STONE_JOINTS" 0 (
      (503.8168 8152.6718) (854.9618 8152.6718)
    ))
    ; P1540 -- see feature_dimensions_mm.csv
    ("05_STONE_JOINTS" 0 (
      (503.8168 8076.3359) (503.8168 8152.6718)
    ))
    ; P1541 -- see feature_dimensions_mm.csv
    ("05_STONE_JOINTS" 0 (
      (503.8168 8076.3359) (793.8931 8076.3359)
    ))
    ; P1542 -- see feature_dimensions_mm.csv
    ("05_STONE_JOINTS" 0 (
      (503.8168 7984.7328) (503.8168 8076.3359)
    ))
    ; P1543 -- see feature_dimensions_mm.csv
    ("05_STONE_JOINTS" 0 (
      (503.8168 7984.7328) (793.8931 7984.7328)
    ))
    ; P1544 -- see feature_dimensions_mm.csv
    ("05_STONE_JOINTS" 0 (
      (503.8168 7893.1298) (503.8168 7984.7328)
    ))
    ; P1545 -- see feature_dimensions_mm.csv
    ("05_STONE_JOINTS" 0 (
      (503.8168 7893.1298) (519.084 7893.1298)
    ))
    ; P1546 -- see feature_dimensions_mm.csv
    ("05_STONE_JOINTS" 0 (
      (503.8168 7557.2519) (519.084 7557.2519)
    ))
    ; P1547 -- see feature_dimensions_mm.csv
    ("05_STONE_JOINTS" 0 (
      (503.8168 7496.1832) (503.8168 7557.2519)
    ))
    ; P1548 -- see feature_dimensions_mm.csv
    ("05_STONE_JOINTS" 0 (
      (503.8168 7496.1832) (854.9618 7496.1832) (854.9618 7541.9847)
    ))
    ; P1549 -- see feature_dimensions_mm.csv
    ("05_STONE_JOINTS" 0 (
      (503.8168 4122.1374) (503.8168 4167.9389)
    ))
    ; P1550 -- see feature_dimensions_mm.csv
    ("05_STONE_JOINTS" 0 (
      (503.8168 4122.1374) (854.9618 4122.1374)
    ))
    ; P1551 -- see feature_dimensions_mm.csv
    ("05_STONE_JOINTS" 0 (
      (503.8168 4045.8015) (503.8168 4122.1374)
    ))
    ; P1552 -- see feature_dimensions_mm.csv
    ("05_STONE_JOINTS" 0 (
      (503.8168 4045.8015) (854.9618 4045.8015)
    ))
    ; P1553 -- see feature_dimensions_mm.csv
    ("05_STONE_JOINTS" 0 (
      (503.8168 3954.1985) (503.8168 4045.8015)
    ))
    ; P1554 -- see feature_dimensions_mm.csv
    ("05_STONE_JOINTS" 0 (
      (503.8168 3954.1985) (854.9618 3954.1985)
    ))
    ; P1555 -- see feature_dimensions_mm.csv
    ("05_STONE_JOINTS" 0 (
      (503.8168 3862.5954) (503.8168 3954.1985)
    ))
    ; P1556 -- see feature_dimensions_mm.csv
    ("05_STONE_JOINTS" 0 (
      (503.8168 3862.5954) (519.084 3862.5954)
    ))
    ; P1557 -- see feature_dimensions_mm.csv
    ("05_STONE_JOINTS" 0 (
      (503.8168 3526.7176) (519.084 3526.7176)
    ))
    ; P1558 -- see feature_dimensions_mm.csv
    ("05_STONE_JOINTS" 0 (
      (503.8168 3450.3817) (503.8168 3526.7176)
    ))
    ; P1559 -- see feature_dimensions_mm.csv
    ("05_STONE_JOINTS" 0 (
      (503.8168 3450.3817) (793.8931 3450.3817)
    ))
    ; P1560 -- see feature_dimensions_mm.csv
    ("05_STONE_JOINTS" 0 (
      (503.8168 3374.0458) (503.8168 3450.3817)
    ))
    ; P1561 -- see feature_dimensions_mm.csv
    ("05_STONE_JOINTS" 0 (
      (503.8168 3374.0458) (793.8931 3374.0458)
    ))
    ; P1562 -- see feature_dimensions_mm.csv
    ("05_STONE_JOINTS" 0 (
      (503.8168 3282.4427) (503.8168 3374.0458)
    ))
    ; P1563 -- see feature_dimensions_mm.csv
    ("05_STONE_JOINTS" 0 (
      (503.8168 3282.4427) (793.8931 3282.4427)
    ))
    ; P1564 -- see feature_dimensions_mm.csv
    ("05_STONE_JOINTS" 0 (
      (503.8168 3190.8397) (503.8168 3282.4427)
    ))
    ; P1565 -- see feature_dimensions_mm.csv
    ("05_STONE_JOINTS" 0 (
      (503.8168 3190.8397) (519.084 3190.8397)
    ))
    ; P1566 -- see feature_dimensions_mm.csv
    ("05_STONE_JOINTS" 0 (
      (503.8168 2854.9618) (519.084 2854.9618)
    ))
    ; P1567 -- see feature_dimensions_mm.csv
    ("05_STONE_JOINTS" 0 (
      (503.8168 2778.626) (503.8168 2854.9618)
    ))
    ; P1568 -- see feature_dimensions_mm.csv
    ("05_STONE_JOINTS" 0 (
      (503.8168 2778.626) (854.9618 2778.626)
    ))
    ; P1569 -- see feature_dimensions_mm.csv
    ("05_STONE_JOINTS" 0 (
      (503.8168 2702.2901) (503.8168 2778.626)
    ))
    ; P1570 -- see feature_dimensions_mm.csv
    ("05_STONE_JOINTS" 0 (
      (503.8168 2702.2901) (854.9618 2702.2901)
    ))
    ; P1571 -- see feature_dimensions_mm.csv
    ("05_STONE_JOINTS" 0 (
      (503.8168 2610.687) (503.8168 2702.2901)
    ))
    ; P1572 -- see feature_dimensions_mm.csv
    ("05_STONE_JOINTS" 0 (
      (503.8168 2610.687) (854.9618 2610.687)
    ))
    ; P1573 -- see feature_dimensions_mm.csv
    ("05_STONE_JOINTS" 0 (
      (503.8168 2519.084) (503.8168 2610.687)
    ))
    ; P1574 -- see feature_dimensions_mm.csv
    ("05_STONE_JOINTS" 0 (
      (503.8168 2519.084) (519.084 2519.084)
    ))
    ; P1575 -- see feature_dimensions_mm.csv
    ("05_STONE_JOINTS" 0 (
      (503.8168 2183.2061) (519.084 2183.2061)
    ))
    ; P1576 -- see feature_dimensions_mm.csv
    ("05_STONE_JOINTS" 0 (
      (503.8168 2106.8702) (503.8168 2183.2061)
    ))
    ; P1577 -- see feature_dimensions_mm.csv
    ("05_STONE_JOINTS" 0 (
      (503.8168 2106.8702) (854.9618 2106.8702)
    ))
    ; P1578 -- see feature_dimensions_mm.csv
    ("05_STONE_JOINTS" 0 (
      (503.8168 2030.5344) (503.8168 2106.8702)
    ))
    ; P1579 -- see feature_dimensions_mm.csv
    ("05_STONE_JOINTS" 0 (
      (503.8168 2030.5344) (854.9618 2030.5344)
    ))
    ; P1580 -- see feature_dimensions_mm.csv
    ("05_STONE_JOINTS" 0 (
      (503.8168 1938.9313) (503.8168 2030.5344)
    ))
    ; P1581 -- see feature_dimensions_mm.csv
    ("05_STONE_JOINTS" 0 (
      (503.8168 1938.9313) (854.9618 1938.9313)
    ))
    ; P1582 -- see feature_dimensions_mm.csv
    ("05_STONE_JOINTS" 0 (
      (503.8168 1847.3282) (503.8168 1938.9313)
    ))
    ; P1583 -- see feature_dimensions_mm.csv
    ("05_STONE_JOINTS" 0 (
      (503.8168 1847.3282) (519.084 1847.3282)
    ))
    ; P1584 -- see feature_dimensions_mm.csv
    ("05_STONE_JOINTS" 0 (
      (503.8168 1511.4504) (519.084 1511.4504)
    ))
    ; P1585 -- see feature_dimensions_mm.csv
    ("05_STONE_JOINTS" 0 (
      (503.8168 1435.1145) (503.8168 1511.4504)
    ))
    ; P1586 -- see feature_dimensions_mm.csv
    ("05_STONE_JOINTS" 0 (
      (503.8168 1435.1145) (854.9618 1435.1145)
    ))
    ; P1587 -- see feature_dimensions_mm.csv
    ("05_STONE_JOINTS" 0 (
      (503.8168 1358.7786) (503.8168 1435.1145)
    ))
    ; P1588 -- see feature_dimensions_mm.csv
    ("05_STONE_JOINTS" 0 (
      (503.8168 1358.7786) (854.9618 1358.7786)
    ))
    ; P1589 -- see feature_dimensions_mm.csv
    ("05_STONE_JOINTS" 0 (
      (503.8168 1267.1756) (503.8168 1358.7786)
    ))
    ; P1590 -- see feature_dimensions_mm.csv
    ("05_STONE_JOINTS" 0 (
      (503.8168 1267.1756) (854.9618 1267.1756)
    ))
    ; P1591 -- see feature_dimensions_mm.csv
    ("05_STONE_JOINTS" 0 (
      (503.8168 1175.5725) (503.8168 1267.1756)
    ))
    ; P1592 -- see feature_dimensions_mm.csv
    ("05_STONE_JOINTS" 0 (
      (503.8168 1175.5725) (519.084 1175.5725)
    ))
    ; P1593 -- see feature_dimensions_mm.csv
    ("05_STONE_JOINTS" 0 (
      (503.8168 839.6947) (519.084 839.6947)
    ))
    ; P1594 -- see feature_dimensions_mm.csv
    ("05_STONE_JOINTS" 0 (
      (503.8168 809.1603) (503.8168 839.6947)
    ))
    ; P1595 -- see feature_dimensions_mm.csv
    ("05_STONE_JOINTS" 0 (
      (503.8168 809.1603) (854.9618 809.1603)
    ))
    ; P1596 -- see feature_dimensions_mm.csv
    ("05_STONE_JOINTS" 0 (
      (519.084 9236.6412) (839.6947 9236.6412)
    ))
    ; P1597 -- see feature_dimensions_mm.csv
    ("05_STONE_JOINTS" 0 (
      (519.084 9160.3053) (519.084 9236.6412)
    ))
    ; P1598 -- see feature_dimensions_mm.csv
    ("05_STONE_JOINTS" 0 (
      (519.084 9083.9695) (519.084 9160.3053)
    ))
    ; P1599 -- see feature_dimensions_mm.csv
    ("05_STONE_JOINTS" 0 (
      (519.084 8992.3664) (519.084 9083.9695)
    ))
    ; P1600 -- see feature_dimensions_mm.csv
    ("05_STONE_JOINTS" 0 (
      (519.084 8900.7634) (519.084 8992.3664)
    ))
    ; P1601 -- see feature_dimensions_mm.csv
    ("05_STONE_JOINTS" 0 (
      (519.084 8900.7634) (839.6947 8900.7634)
    ))
    ; P1602 -- see feature_dimensions_mm.csv
    ("05_STONE_JOINTS" 0 (
      (519.084 8564.8855) (839.6947 8564.8855)
    ))
    ; P1603 -- see feature_dimensions_mm.csv
    ("05_STONE_JOINTS" 0 (
      (519.084 8488.5496) (519.084 8564.8855)
    ))
    ; P1604 -- see feature_dimensions_mm.csv
    ("05_STONE_JOINTS" 0 (
      (519.084 8412.2137) (519.084 8488.5496)
    ))
    ; P1605 -- see feature_dimensions_mm.csv
    ("05_STONE_JOINTS" 0 (
      (519.084 8320.6107) (519.084 8412.2137)
    ))
    ; P1606 -- see feature_dimensions_mm.csv
    ("05_STONE_JOINTS" 0 (
      (519.084 8229.0076) (519.084 8320.6107)
    ))
    ; P1607 -- see feature_dimensions_mm.csv
    ("05_STONE_JOINTS" 0 (
      (519.084 8229.0076) (839.6947 8229.0076)
    ))
    ; P1608 -- see feature_dimensions_mm.csv
    ("05_STONE_JOINTS" 0 (
      (519.084 7893.1298) (793.8931 7893.1298)
    ))
    ; P1609 -- see feature_dimensions_mm.csv
    ("05_STONE_JOINTS" 0 (
      (519.084 7816.7939) (519.084 7893.1298)
    ))
    ; P1610 -- see feature_dimensions_mm.csv
    ("05_STONE_JOINTS" 0 (
      (519.084 7740.458) (519.084 7816.7939)
    ))
    ; P1611 -- see feature_dimensions_mm.csv
    ("05_STONE_JOINTS" 0 (
      (519.084 7648.855) (519.084 7740.458)
    ))
    ; P1612 -- see feature_dimensions_mm.csv
    ("05_STONE_JOINTS" 0 (
      (519.084 7557.2519) (519.084 7648.855)
    ))
    ; P1613 -- see feature_dimensions_mm.csv
    ("05_STONE_JOINTS" 0 (
      (519.084 7557.2519) (793.8931 7557.2519)
    ))
    ; P1614 -- see feature_dimensions_mm.csv
    ("05_STONE_JOINTS" 0 (
      (839.6947 5847.3282) (519.084 5847.3282)
    ))
    ; P1615 -- see feature_dimensions_mm.csv
    ("05_STONE_JOINTS" 0 (
      (519.084 5816.7939) (519.084 5847.3282)
    ))
    ; P1616 -- see feature_dimensions_mm.csv
    ("05_STONE_JOINTS" 0 (
      (519.084 5816.7939) (839.6947 5816.7939)
    ))
    ; P1617 -- see feature_dimensions_mm.csv
    ("05_STONE_JOINTS" 0 (
      (519.084 3862.5954) (839.6947 3862.5954)
    ))
    ; P1618 -- see feature_dimensions_mm.csv
    ("05_STONE_JOINTS" 0 (
      (519.084 3786.2595) (519.084 3862.5954)
    ))
    ; P1619 -- see feature_dimensions_mm.csv
    ("05_STONE_JOINTS" 0 (
      (519.084 3709.9237) (519.084 3786.2595)
    ))
    ; P1620 -- see feature_dimensions_mm.csv
    ("05_STONE_JOINTS" 0 (
      (519.084 3618.3206) (519.084 3709.9237)
    ))
    ; P1621 -- see feature_dimensions_mm.csv
    ("05_STONE_JOINTS" 0 (
      (519.084 3526.7176) (519.084 3618.3206)
    ))
    ; P1622 -- see feature_dimensions_mm.csv
    ("05_STONE_JOINTS" 0 (
      (519.084 3526.7176) (793.8931 3526.7176)
    ))
    ; P1623 -- see feature_dimensions_mm.csv
    ("05_STONE_JOINTS" 0 (
      (519.084 3190.8397) (839.6947 3190.8397)
    ))
    ; P1624 -- see feature_dimensions_mm.csv
    ("05_STONE_JOINTS" 0 (
      (519.084 3114.5038) (519.084 3190.8397)
    ))
    ; P1625 -- see feature_dimensions_mm.csv
    ("05_STONE_JOINTS" 0 (
      (519.084 3038.1679) (519.084 3114.5038)
    ))
    ; P1626 -- see feature_dimensions_mm.csv
    ("05_STONE_JOINTS" 0 (
      (519.084 2946.5649) (519.084 3038.1679)
    ))
    ; P1627 -- see feature_dimensions_mm.csv
    ("05_STONE_JOINTS" 0 (
      (519.084 2854.9618) (519.084 2946.5649)
    ))
    ; P1628 -- see feature_dimensions_mm.csv
    ("05_STONE_JOINTS" 0 (
      (519.084 2854.9618) (839.6947 2854.9618)
    ))
    ; P1629 -- see feature_dimensions_mm.csv
    ("05_STONE_JOINTS" 0 (
      (519.084 2519.084) (839.6947 2519.084)
    ))
    ; P1630 -- see feature_dimensions_mm.csv
    ("05_STONE_JOINTS" 0 (
      (519.084 2442.7481) (519.084 2519.084)
    ))
    ; P1631 -- see feature_dimensions_mm.csv
    ("05_STONE_JOINTS" 0 (
      (519.084 2366.4122) (519.084 2442.7481)
    ))
    ; P1632 -- see feature_dimensions_mm.csv
    ("05_STONE_JOINTS" 0 (
      (519.084 2274.8092) (519.084 2366.4122)
    ))
    ; P1633 -- see feature_dimensions_mm.csv
    ("05_STONE_JOINTS" 0 (
      (519.084 2183.2061) (519.084 2274.8092)
    ))
    ; P1634 -- see feature_dimensions_mm.csv
    ("05_STONE_JOINTS" 0 (
      (519.084 2183.2061) (839.6947 2183.2061)
    ))
    ; P1635 -- see feature_dimensions_mm.csv
    ("05_STONE_JOINTS" 0 (
      (519.084 1847.3282) (839.6947 1847.3282)
    ))
    ; P1636 -- see feature_dimensions_mm.csv
    ("05_STONE_JOINTS" 0 (
      (519.084 1770.9924) (519.084 1847.3282)
    ))
    ; P1637 -- see feature_dimensions_mm.csv
    ("05_STONE_JOINTS" 0 (
      (519.084 1694.6565) (519.084 1770.9924)
    ))
    ; P1638 -- see feature_dimensions_mm.csv
    ("05_STONE_JOINTS" 0 (
      (519.084 1770.9924) (183.2061 1770.9924) (183.2061 1694.6565) (519.084 1694.6565)
    ))
    ; P1639 -- see feature_dimensions_mm.csv
    ("05_STONE_JOINTS" 0 (
      (519.084 1603.0534) (519.084 1694.6565)
    ))
    ; P1640 -- see feature_dimensions_mm.csv
    ("05_STONE_JOINTS" 0 (
      (519.084 1511.4504) (519.084 1603.0534)
    ))
    ; P1641 -- see feature_dimensions_mm.csv
    ("05_STONE_JOINTS" 0 (
      (519.084 1511.4504) (839.6947 1511.4504)
    ))
    ; P1642 -- see feature_dimensions_mm.csv
    ("05_STONE_JOINTS" 0 (
      (519.084 1175.5725) (839.6947 1175.5725)
    ))
    ; P1643 -- see feature_dimensions_mm.csv
    ("05_STONE_JOINTS" 0 (
      (519.084 1099.2366) (519.084 1175.5725)
    ))
    ; P1644 -- see feature_dimensions_mm.csv
    ("05_STONE_JOINTS" 0 (
      (519.084 1022.9008) (519.084 1099.2366)
    ))
    ; P1645 -- see feature_dimensions_mm.csv
    ("05_STONE_JOINTS" 0 (
      (519.084 931.2977) (519.084 1022.9008)
    ))
    ; P1646 -- see feature_dimensions_mm.csv
    ("05_STONE_JOINTS" 0 (
      (519.084 839.6947) (519.084 931.2977)
    ))
    ; P1647 -- see feature_dimensions_mm.csv
    ("05_STONE_JOINTS" 0 (
      (519.084 839.6947) (839.6947 839.6947)
    ))
    ; P1648 -- see feature_dimensions_mm.csv
    ("05_STONE_JOINTS" 0 (
      (793.8931 8076.3359) (854.9618 8076.3359)
    ))
    ; P1649 -- see feature_dimensions_mm.csv
    ("05_STONE_JOINTS" 0 (
      (793.8931 7984.7328) (793.8931 8076.3359)
    ))
    ; P1650 -- see feature_dimensions_mm.csv
    ("05_STONE_JOINTS" 0 (
      (793.8931 7893.1298) (793.8931 7984.7328)
    ))
    ; P1651 -- see feature_dimensions_mm.csv
    ("05_STONE_JOINTS" 0 (
      (793.8931 7557.2519) (793.8931 7740.458) (793.8931 7893.1298)
    ))
    ; P1652 -- see feature_dimensions_mm.csv
    ("05_STONE_JOINTS" 0 (
      (854.9618 7541.9847) (793.8931 7541.9847) (793.8931 7557.2519)
    ))
    ; P1653 -- see feature_dimensions_mm.csv
    ("05_STONE_JOINTS" 0 (
      (793.8931 3450.3817) (793.8931 3526.7176)
    ))
    ; P1654 -- see feature_dimensions_mm.csv
    ("05_STONE_JOINTS" 0 (
      (793.8931 3526.7176) (793.8931 3633.5878) (839.6947 3633.5878) (839.6947 3709.9237)
    ))
    ; P1655 -- see feature_dimensions_mm.csv
    ("05_STONE_JOINTS" 0 (
      (793.8931 3374.0458) (793.8931 3419.8473) (793.8931 3450.3817)
    ))
    ; P1656 -- see feature_dimensions_mm.csv
    ("05_STONE_JOINTS" 0 (
      (793.8931 3282.4427) (793.8931 3374.0458)
    ))
    ; P1657 -- see feature_dimensions_mm.csv
    ("05_STONE_JOINTS" 0 (
      (854.9618 3267.1756) (793.8931 3267.1756) (793.8931 3282.4427)
    ))
    ; P1658 -- see feature_dimensions_mm.csv
    ("05_STONE_JOINTS" 0 (
      (839.6947 9236.6412) (854.9618 9236.6412)
    ))
    ; P1659 -- see feature_dimensions_mm.csv
    ("05_STONE_JOINTS" 0 (
      (839.6947 9160.3053) (839.6947 9236.6412)
    ))
    ; P1660 -- see feature_dimensions_mm.csv
    ("05_STONE_JOINTS" 0 (
      (839.6947 9160.3053) (1190.8397 9160.3053)
    ))
    ; P1661 -- see feature_dimensions_mm.csv
    ("05_STONE_JOINTS" 0 (
      (839.6947 9083.9695) (839.6947 9160.3053)
    ))
    ; P1662 -- see feature_dimensions_mm.csv
    ("05_STONE_JOINTS" 0 (
      (839.6947 9083.9695) (1190.8397 9083.9695)
    ))
    ; P1663 -- see feature_dimensions_mm.csv
    ("05_STONE_JOINTS" 0 (
      (839.6947 8992.3664) (839.6947 9083.9695)
    ))
    ; P1664 -- see feature_dimensions_mm.csv
    ("05_STONE_JOINTS" 0 (
      (839.6947 8992.3664) (1190.8397 8992.3664)
    ))
    ; P1665 -- see feature_dimensions_mm.csv
    ("05_STONE_JOINTS" 0 (
      (839.6947 8900.7634) (839.6947 8992.3664)
    ))
    ; P1666 -- see feature_dimensions_mm.csv
    ("05_STONE_JOINTS" 0 (
      (839.6947 8900.7634) (854.9618 8900.7634)
    ))
    ; P1667 -- see feature_dimensions_mm.csv
    ("05_STONE_JOINTS" 0 (
      (839.6947 8564.8855) (854.9618 8564.8855)
    ))
    ; P1668 -- see feature_dimensions_mm.csv
    ("05_STONE_JOINTS" 0 (
      (839.6947 8488.5496) (839.6947 8564.8855)
    ))
    ; P1669 -- see feature_dimensions_mm.csv
    ("05_STONE_JOINTS" 0 (
      (839.6947 8488.5496) (1190.8397 8488.5496)
    ))
    ; P1670 -- see feature_dimensions_mm.csv
    ("05_STONE_JOINTS" 0 (
      (839.6947 8412.2137) (839.6947 8488.5496)
    ))
    ; P1671 -- see feature_dimensions_mm.csv
    ("05_STONE_JOINTS" 0 (
      (839.6947 8412.2137) (1190.8397 8412.2137)
    ))
    ; P1672 -- see feature_dimensions_mm.csv
    ("05_STONE_JOINTS" 0 (
      (839.6947 8320.6107) (839.6947 8412.2137)
    ))
    ; P1673 -- see feature_dimensions_mm.csv
    ("05_STONE_JOINTS" 0 (
      (839.6947 8320.6107) (1190.8397 8320.6107)
    ))
    ; P1674 -- see feature_dimensions_mm.csv
    ("05_STONE_JOINTS" 0 (
      (839.6947 8229.0076) (839.6947 8320.6107)
    ))
    ; P1675 -- see feature_dimensions_mm.csv
    ("05_STONE_JOINTS" 0 (
      (839.6947 8229.0076) (854.9618 8229.0076)
    ))
    ; P1676 -- see feature_dimensions_mm.csv
    ("05_STONE_JOINTS" 0 (
      (900.7634 5877.8626) (900.7634 5847.3282) (839.6947 5847.3282)
    ))
    ; P1677 -- see feature_dimensions_mm.csv
    ("05_STONE_JOINTS" 0 (
      (839.6947 5816.7939) (839.6947 5847.3282)
    ))
    ; P1678 -- see feature_dimensions_mm.csv
    ("05_STONE_JOINTS" 0 (
      (839.6947 5816.7939) (900.7634 5816.7939) (900.7634 5801.5267)
    ))
    ; P1679 -- see feature_dimensions_mm.csv
    ("05_STONE_JOINTS" 0 (
      (839.6947 3862.5954) (854.9618 3862.5954)
    ))
    ; P1680 -- see feature_dimensions_mm.csv
    ("05_STONE_JOINTS" 0 (
      (839.6947 3786.2595) (839.6947 3862.5954)
    ))
    ; P1681 -- see feature_dimensions_mm.csv
    ("05_STONE_JOINTS" 0 (
      (839.6947 3786.2595) (961.8321 3786.2595)
    ))
    ; P1682 -- see feature_dimensions_mm.csv
    ("05_STONE_JOINTS" 0 (
      (839.6947 3709.9237) (839.6947 3786.2595)
    ))
    ; P1683 -- see feature_dimensions_mm.csv
    ("05_STONE_JOINTS" 0 (
      (839.6947 3709.9237) (931.2977 3709.9237) (961.8321 3709.9237)
    ))
    ; P1684 -- see feature_dimensions_mm.csv
    ("05_STONE_JOINTS" 0 (
      (839.6947 3190.8397) (854.9618 3190.8397)
    ))
    ; P1685 -- see feature_dimensions_mm.csv
    ("05_STONE_JOINTS" 0 (
      (839.6947 3114.5038) (839.6947 3190.8397)
    ))
    ; P1686 -- see feature_dimensions_mm.csv
    ("05_STONE_JOINTS" 0 (
      (839.6947 3114.5038) (961.8321 3114.5038)
    ))
    ; P1687 -- see feature_dimensions_mm.csv
    ("05_STONE_JOINTS" 0 (
      (839.6947 3038.1679) (839.6947 3114.5038)
    ))
    ; P1688 -- see feature_dimensions_mm.csv
    ("05_STONE_JOINTS" 0 (
      (839.6947 3038.1679) (961.8321 3038.1679)
    ))
    ; P1689 -- see feature_dimensions_mm.csv
    ("05_STONE_JOINTS" 0 (
      (839.6947 2946.5649) (839.6947 3038.1679)
    ))
    ; P1690 -- see feature_dimensions_mm.csv
    ("05_STONE_JOINTS" 0 (
      (839.6947 2946.5649) (961.8321 2946.5649)
    ))
    ; P1691 -- see feature_dimensions_mm.csv
    ("05_STONE_JOINTS" 0 (
      (839.6947 2854.9618) (839.6947 2946.5649)
    ))
    ; P1692 -- see feature_dimensions_mm.csv
    ("05_STONE_JOINTS" 0 (
      (839.6947 2854.9618) (854.9618 2854.9618)
    ))
    ; P1693 -- see feature_dimensions_mm.csv
    ("05_STONE_JOINTS" 0 (
      (839.6947 2519.084) (854.9618 2519.084)
    ))
    ; P1694 -- see feature_dimensions_mm.csv
    ("05_STONE_JOINTS" 0 (
      (839.6947 2442.7481) (839.6947 2519.084)
    ))
    ; P1695 -- see feature_dimensions_mm.csv
    ("05_STONE_JOINTS" 0 (
      (839.6947 2442.7481) (961.8321 2442.7481)
    ))
    ; P1696 -- see feature_dimensions_mm.csv
    ("05_STONE_JOINTS" 0 (
      (839.6947 2366.4122) (839.6947 2442.7481)
    ))
    ; P1697 -- see feature_dimensions_mm.csv
    ("05_STONE_JOINTS" 0 (
      (839.6947 2366.4122) (961.8321 2366.4122)
    ))
    ; P1698 -- see feature_dimensions_mm.csv
    ("05_STONE_JOINTS" 0 (
      (839.6947 2274.8092) (839.6947 2366.4122)
    ))
    ; P1699 -- see feature_dimensions_mm.csv
    ("05_STONE_JOINTS" 0 (
      (839.6947 2274.8092) (961.8321 2274.8092)
    ))
    ; P1700 -- see feature_dimensions_mm.csv
    ("05_STONE_JOINTS" 0 (
      (839.6947 2183.2061) (839.6947 2274.8092)
    ))
    ; P1701 -- see feature_dimensions_mm.csv
    ("05_STONE_JOINTS" 0 (
      (839.6947 2183.2061) (854.9618 2183.2061)
    ))
    ; P1702 -- see feature_dimensions_mm.csv
    ("05_STONE_JOINTS" 0 (
      (839.6947 1847.3282) (854.9618 1847.3282)
    ))
    ; P1703 -- see feature_dimensions_mm.csv
    ("05_STONE_JOINTS" 0 (
      (839.6947 1770.9924) (839.6947 1847.3282)
    ))
    ; P1704 -- see feature_dimensions_mm.csv
    ("05_STONE_JOINTS" 0 (
      (839.6947 1770.9924) (961.8321 1770.9924)
    ))
    ; P1705 -- see feature_dimensions_mm.csv
    ("05_STONE_JOINTS" 0 (
      (839.6947 1694.6565) (839.6947 1770.9924)
    ))
    ; P1706 -- see feature_dimensions_mm.csv
    ("05_STONE_JOINTS" 0 (
      (839.6947 1694.6565) (961.8321 1694.6565)
    ))
    ; P1707 -- see feature_dimensions_mm.csv
    ("05_STONE_JOINTS" 0 (
      (839.6947 1603.0534) (839.6947 1694.6565)
    ))
    ; P1708 -- see feature_dimensions_mm.csv
    ("05_STONE_JOINTS" 0 (
      (839.6947 1603.0534) (961.8321 1603.0534)
    ))
    ; P1709 -- see feature_dimensions_mm.csv
    ("05_STONE_JOINTS" 0 (
      (839.6947 1511.4504) (839.6947 1603.0534)
    ))
    ; P1710 -- see feature_dimensions_mm.csv
    ("05_STONE_JOINTS" 0 (
      (839.6947 1511.4504) (854.9618 1511.4504)
    ))
    ; P1711 -- see feature_dimensions_mm.csv
    ("05_STONE_JOINTS" 0 (
      (839.6947 1175.5725) (854.9618 1175.5725)
    ))
    ; P1712 -- see feature_dimensions_mm.csv
    ("05_STONE_JOINTS" 0 (
      (839.6947 1099.2366) (839.6947 1175.5725)
    ))
    ; P1713 -- see feature_dimensions_mm.csv
    ("05_STONE_JOINTS" 0 (
      (839.6947 1099.2366) (961.8321 1099.2366)
    ))
    ; P1714 -- see feature_dimensions_mm.csv
    ("05_STONE_JOINTS" 0 (
      (839.6947 1022.9008) (839.6947 1099.2366)
    ))
    ; P1715 -- see feature_dimensions_mm.csv
    ("05_STONE_JOINTS" 0 (
      (839.6947 1022.9008) (961.8321 1022.9008)
    ))
    ; P1716 -- see feature_dimensions_mm.csv
    ("05_STONE_JOINTS" 0 (
      (839.6947 931.2977) (839.6947 1022.9008)
    ))
    ; P1717 -- see feature_dimensions_mm.csv
    ("05_STONE_JOINTS" 0 (
      (839.6947 931.2977) (961.8321 931.2977)
    ))
    ; P1718 -- see feature_dimensions_mm.csv
    ("05_STONE_JOINTS" 0 (
      (839.6947 839.6947) (839.6947 931.2977)
    ))
    ; P1719 -- see feature_dimensions_mm.csv
    ("05_STONE_JOINTS" 0 (
      (839.6947 839.6947) (854.9618 839.6947)
    ))
    ; P1720 -- see feature_dimensions_mm.csv
    ("05_STONE_JOINTS" 0 (
      (1175.5725 9572.5191) (854.9618 9572.5191)
    ))
    ; P1721 -- see feature_dimensions_mm.csv
    ("05_STONE_JOINTS" 0 (
      (854.9618 9496.1832) (854.9618 9557.2519) (854.9618 9572.5191)
    ))
    ; P1722 -- see feature_dimensions_mm.csv
    ("05_STONE_JOINTS" 0 (
      (854.9618 9419.8473) (854.9618 9496.1832)
    ))
    ; P1723 -- see feature_dimensions_mm.csv
    ("05_STONE_JOINTS" 0 (
      (854.9618 9328.2443) (854.9618 9419.8473)
    ))
    ; P1724 -- see feature_dimensions_mm.csv
    ("05_STONE_JOINTS" 0 (
      (854.9618 9236.6412) (854.9618 9328.2443)
    ))
    ; P1725 -- see feature_dimensions_mm.csv
    ("05_STONE_JOINTS" 0 (
      (854.9618 9236.6412) (1175.5725 9236.6412)
    ))
    ; P1726 -- see feature_dimensions_mm.csv
    ("05_STONE_JOINTS" 0 (
      (854.9618 8900.7634) (1175.5725 8900.7634)
    ))
    ; P1727 -- see feature_dimensions_mm.csv
    ("05_STONE_JOINTS" 0 (
      (854.9618 8824.4275) (854.9618 8900.7634)
    ))
    ; P1728 -- see feature_dimensions_mm.csv
    ("05_STONE_JOINTS" 0 (
      (854.9618 8748.0916) (854.9618 8824.4275)
    ))
    ; P1729 -- see feature_dimensions_mm.csv
    ("05_STONE_JOINTS" 0 (
      (854.9618 8656.4885) (854.9618 8748.0916)
    ))
    ; P1730 -- see feature_dimensions_mm.csv
    ("05_STONE_JOINTS" 0 (
      (854.9618 8564.8855) (854.9618 8656.4885)
    ))
    ; P1731 -- see feature_dimensions_mm.csv
    ("05_STONE_JOINTS" 0 (
      (854.9618 8564.8855) (1175.5725 8564.8855)
    ))
    ; P1732 -- see feature_dimensions_mm.csv
    ("05_STONE_JOINTS" 0 (
      (854.9618 8229.0076) (1175.5725 8229.0076)
    ))
    ; P1733 -- see feature_dimensions_mm.csv
    ("05_STONE_JOINTS" 0 (
      (854.9618 8152.6718) (854.9618 8229.0076)
    ))
    ; P1734 -- see feature_dimensions_mm.csv
    ("05_STONE_JOINTS" 0 (
      (854.9618 8076.3359) (854.9618 8152.6718)
    ))
    ; P1735 -- see feature_dimensions_mm.csv
    ("05_STONE_JOINTS" 0 (
      (854.9618 8076.3359) (1021.5267 8076.3359) (1175.5725 8076.3359)
    ))
    ; P1736 -- see feature_dimensions_mm.csv
    ("05_STONE_JOINTS" 0 (
      (961.8321 7541.9847) (854.9618 7541.9847)
    ))
    ; P1737 -- see feature_dimensions_mm.csv
    ("05_STONE_JOINTS" 0 (
      (854.9618 4122.1374) (854.9618 4167.9389)
    ))
    ; P1738 -- see feature_dimensions_mm.csv
    ("05_STONE_JOINTS" 0 (
      (854.9618 4045.8015) (854.9618 4122.1374)
    ))
    ; P1739 -- see feature_dimensions_mm.csv
    ("05_STONE_JOINTS" 0 (
      (854.9618 3954.1985) (854.9618 4045.8015)
    ))
    ; P1740 -- see feature_dimensions_mm.csv
    ("05_STONE_JOINTS" 0 (
      (854.9618 3862.5954) (854.9618 3954.1985)
    ))
    ; P1741 -- see feature_dimensions_mm.csv
    ("05_STONE_JOINTS" 0 (
      (854.9618 3862.5954) (961.8321 3862.5954) (961.8321 3786.2595)
    ))
    ; P1742 -- see feature_dimensions_mm.csv
    ("05_STONE_JOINTS" 0 (
      (854.9618 3267.1756) (961.8321 3267.1756) (961.8321 3190.8397)
    ))
    ; P1743 -- see feature_dimensions_mm.csv
    ("05_STONE_JOINTS" 0 (
      (854.9618 3190.8397) (854.9618 3267.1756)
    ))
    ; P1744 -- see feature_dimensions_mm.csv
    ("05_STONE_JOINTS" 0 (
      (854.9618 3190.8397) (961.8321 3190.8397)
    ))
    ; P1745 -- see feature_dimensions_mm.csv
    ("05_STONE_JOINTS" 0 (
      (854.9618 2854.9618) (961.8321 2854.9618)
    ))
    ; P1746 -- see feature_dimensions_mm.csv
    ("05_STONE_JOINTS" 0 (
      (854.9618 2778.626) (854.9618 2854.9618)
    ))
    ; P1747 -- see feature_dimensions_mm.csv
    ("05_STONE_JOINTS" 0 (
      (854.9618 2702.2901) (854.9618 2778.626)
    ))
    ; P1748 -- see feature_dimensions_mm.csv
    ("05_STONE_JOINTS" 0 (
      (854.9618 2610.687) (854.9618 2702.2901)
    ))
    ; P1749 -- see feature_dimensions_mm.csv
    ("05_STONE_JOINTS" 0 (
      (854.9618 2519.084) (854.9618 2610.687)
    ))
    ; P1750 -- see feature_dimensions_mm.csv
    ("05_STONE_JOINTS" 0 (
      (854.9618 2519.084) (961.8321 2519.084)
    ))
    ; P1751 -- see feature_dimensions_mm.csv
    ("05_STONE_JOINTS" 0 (
      (854.9618 2183.2061) (961.8321 2183.2061)
    ))
    ; P1752 -- see feature_dimensions_mm.csv
    ("05_STONE_JOINTS" 0 (
      (854.9618 2106.8702) (854.9618 2183.2061)
    ))
    ; P1753 -- see feature_dimensions_mm.csv
    ("05_STONE_JOINTS" 0 (
      (854.9618 2030.5344) (854.9618 2106.8702)
    ))
    ; P1754 -- see feature_dimensions_mm.csv
    ("05_STONE_JOINTS" 0 (
      (854.9618 1938.9313) (854.9618 2030.5344)
    ))
    ; P1755 -- see feature_dimensions_mm.csv
    ("05_STONE_JOINTS" 0 (
      (854.9618 1847.3282) (854.9618 1938.9313)
    ))
    ; P1756 -- see feature_dimensions_mm.csv
    ("05_STONE_JOINTS" 0 (
      (854.9618 1847.3282) (961.8321 1847.3282)
    ))
    ; P1757 -- see feature_dimensions_mm.csv
    ("05_STONE_JOINTS" 0 (
      (854.9618 1511.4504) (961.8321 1511.4504)
    ))
    ; P1758 -- see feature_dimensions_mm.csv
    ("05_STONE_JOINTS" 0 (
      (854.9618 1435.1145) (854.9618 1511.4504)
    ))
    ; P1759 -- see feature_dimensions_mm.csv
    ("05_STONE_JOINTS" 0 (
      (854.9618 1358.7786) (854.9618 1435.1145)
    ))
    ; P1760 -- see feature_dimensions_mm.csv
    ("05_STONE_JOINTS" 0 (
      (854.9618 1267.1756) (854.9618 1358.7786)
    ))
    ; P1761 -- see feature_dimensions_mm.csv
    ("05_STONE_JOINTS" 0 (
      (854.9618 1175.5725) (854.9618 1267.1756)
    ))
    ; P1762 -- see feature_dimensions_mm.csv
    ("05_STONE_JOINTS" 0 (
      (854.9618 1175.5725) (961.8321 1175.5725)
    ))
    ; P1763 -- see feature_dimensions_mm.csv
    ("05_STONE_JOINTS" 0 (
      (854.9618 839.6947) (961.8321 839.6947)
    ))
    ; P1764 -- see feature_dimensions_mm.csv
    ("05_STONE_JOINTS" 0 (
      (854.9618 809.1603) (854.9618 839.6947)
    ))
    ; P1765 -- see feature_dimensions_mm.csv
    ("05_STONE_JOINTS" 0 (
      (854.9618 809.1603) (961.8321 809.1603)
    ))
    ; P1766 -- see feature_dimensions_mm.csv
    ("05_STONE_JOINTS" 0 (
      (900.7634 7221.374) (961.8321 7221.374) (961.8321 7145.0382)
    ))
    ; P1767 -- see feature_dimensions_mm.csv
    ("05_STONE_JOINTS" 0 (
      (900.7634 7145.0382) (961.8321 7145.0382)
    ))
    ; P1768 -- see feature_dimensions_mm.csv
    ("05_STONE_JOINTS" 0 (
      (900.7634 7068.7023) (961.8321 7068.7023)
    ))
    ; P1769 -- see feature_dimensions_mm.csv
    ("05_STONE_JOINTS" 0 (
      (900.7634 6885.4962) (946.5649 6885.4962) (961.8321 6885.4962)
    ))
    ; P1770 -- see feature_dimensions_mm.csv
    ("05_STONE_JOINTS" 0 (
      (900.7634 6885.4962) (900.7634 6549.6183)
    ))
    ; P1771 -- see feature_dimensions_mm.csv
    ("05_STONE_JOINTS" 0 (
      (900.7634 6885.4962) (900.7634 6977.0992) (946.5649 6977.0992)
    ))
    ; P1772 -- see feature_dimensions_mm.csv
    ("05_STONE_JOINTS" 0 (
      (900.7634 6549.6183) (961.8321 6549.6183)
    ))
    ; P1773 -- see feature_dimensions_mm.csv
    ("05_STONE_JOINTS" 0 (
      (900.7634 6549.6183) (900.7634 6473.2824)
    ))
    ; P1774 -- see feature_dimensions_mm.csv
    ("05_STONE_JOINTS" 0 (
      (900.7634 6473.2824) (961.8321 6473.2824)
    ))
    ; P1775 -- see feature_dimensions_mm.csv
    ("05_STONE_JOINTS" 0 (
      (900.7634 6473.2824) (900.7634 6396.9466)
    ))
    ; P1776 -- see feature_dimensions_mm.csv
    ("05_STONE_JOINTS" 0 (
      (900.7634 6396.9466) (961.8321 6396.9466)
    ))
    ; P1777 -- see feature_dimensions_mm.csv
    ("05_STONE_JOINTS" 0 (
      (900.7634 6396.9466) (900.7634 6305.3435)
    ))
    ; P1778 -- see feature_dimensions_mm.csv
    ("05_STONE_JOINTS" 0 (
      (900.7634 6305.3435) (961.8321 6305.3435) (961.8321 6213.7405)
    ))
    ; P1779 -- see feature_dimensions_mm.csv
    ("05_STONE_JOINTS" 0 (
      (900.7634 6305.3435) (900.7634 6213.7405)
    ))
    ; P1780 -- see feature_dimensions_mm.csv
    ("05_STONE_JOINTS" 0 (
      (900.7634 6213.7405) (961.8321 6213.7405)
    ))
    ; P1781 -- see feature_dimensions_mm.csv
    ("05_STONE_JOINTS" 0 (
      (900.7634 6213.7405) (900.7634 5877.8626)
    ))
    ; P1782 -- see feature_dimensions_mm.csv
    ("05_STONE_JOINTS" 0 (
      (900.7634 5877.8626) (961.8321 5877.8626)
    ))
    ; P1783 -- see feature_dimensions_mm.csv
    ("05_STONE_JOINTS" 0 (
      (900.7634 5801.5267) (961.8321 5801.5267)
    ))
    ; P1784 -- see feature_dimensions_mm.csv
    ("05_STONE_JOINTS" 0 (
      (900.7634 5801.5267) (900.7634 5725.1908)
    ))
    ; P1785 -- see feature_dimensions_mm.csv
    ("05_STONE_JOINTS" 0 (
      (900.7634 5725.1908) (961.8321 5725.1908)
    ))
    ; P1786 -- see feature_dimensions_mm.csv
    ("05_STONE_JOINTS" 0 (
      (900.7634 5725.1908) (900.7634 5633.5878)
    ))
    ; P1787 -- see feature_dimensions_mm.csv
    ("05_STONE_JOINTS" 0 (
      (900.7634 5633.5878) (961.8321 5633.5878)
    ))
    ; P1788 -- see feature_dimensions_mm.csv
    ("05_STONE_JOINTS" 0 (
      (900.7634 5633.5878) (900.7634 5541.9847) (961.8321 5541.9847)
    ))
    ; P1789 -- see feature_dimensions_mm.csv
    ("05_STONE_JOINTS" 0 (
      (900.7634 5206.1069) (961.8321 5206.1069)
    ))
    ; P1790 -- see feature_dimensions_mm.csv
    ("05_STONE_JOINTS" 0 (
      (900.7634 5129.771) (961.8321 5129.771)
    ))
    ; P1791 -- see feature_dimensions_mm.csv
    ("05_STONE_JOINTS" 0 (
      (900.7634 5053.4351) (961.8321 5053.4351)
    ))
    ; P1792 -- see feature_dimensions_mm.csv
    ("05_STONE_JOINTS" 0 (
      (900.7634 4961.8321) (961.8321 4961.8321)
    ))
    ; P1793 -- see feature_dimensions_mm.csv
    ("05_STONE_JOINTS" 0 (
      (900.7634 4870.229) (961.8321 4870.229)
    ))
    ; P1794 -- see feature_dimensions_mm.csv
    ("05_STONE_JOINTS" 0 (
      (900.7634 4534.3511) (961.8321 4534.3511)
    ))
    ; P1795 -- see feature_dimensions_mm.csv
    ("05_STONE_JOINTS" 0 (
      (900.7634 4458.0153) (961.8321 4458.0153)
    ))
    ; P1796 -- see feature_dimensions_mm.csv
    ("05_STONE_JOINTS" 0 (
      (900.7634 4381.6794) (961.8321 4381.6794)
    ))
    ; P1797 -- see feature_dimensions_mm.csv
    ("05_STONE_JOINTS" 0 (
      (900.7634 4290.0763) (961.8321 4290.0763)
    ))
    ; P1798 -- see feature_dimensions_mm.csv
    ("05_STONE_JOINTS" 0 (
      (900.7634 4198.4733) (961.8321 4198.4733)
    ))
    ; P1799 -- see feature_dimensions_mm.csv
    ("05_STONE_JOINTS" 0 (
      (5160.3053 7679.3893) (5160.3053 7541.9847) (4992.3664 7541.9847) (961.8321 7541.9847)
    ))
    ; P1800 -- see feature_dimensions_mm.csv
    ("05_STONE_JOINTS" 0 (
      (961.8321 7541.9847) (961.8321 7526.7176) (4992.3664 7526.7176) (4992.3664 7374.0458) (4992.3664 7358.7786)
    ))
    ; P1801 -- see feature_dimensions_mm.csv
    ("05_STONE_JOINTS" 0 (
      (961.8321 7145.0382) (961.8321 7068.7023)
    ))
    ; P1802 -- see feature_dimensions_mm.csv
    ("05_STONE_JOINTS" 0 (
      (961.8321 7068.7023) (961.8321 6992.3664)
    ))
    ; P1803 -- see feature_dimensions_mm.csv
    ("05_STONE_JOINTS" 0 (
      (961.8321 6885.4962) (961.8321 6656.4885) (961.8321 6564.8855) (4992.3664 6564.8855) (4992.3664 6625.9542)
      (4992.3664 6656.4885) (4992.3664 6961.8321) (4992.3664 6977.0992) (4992.3664 6992.3664) (961.8321 6992.3664)
    ))
    ; P1804 -- see feature_dimensions_mm.csv
    ("05_STONE_JOINTS" 0 (
      (961.8321 6992.3664) (961.8321 6977.0992) (961.8321 6885.4962)
    ))
    ; P1805 -- see feature_dimensions_mm.csv
    ("05_STONE_JOINTS" 0 (
      (961.8321 6213.7405) (961.8321 5969.4656)
    ))
    ; P1806 -- see feature_dimensions_mm.csv
    ("05_STONE_JOINTS" 0 (
      (961.8321 5969.4656) (1358.7786 5969.4656) (1358.7786 5816.7939)
    ))
    ; P1807 -- see feature_dimensions_mm.csv
    ("05_STONE_JOINTS" 0 (
      (961.8321 5969.4656) (961.8321 5877.8626)
    ))
    ; P1808 -- see feature_dimensions_mm.csv
    ("05_STONE_JOINTS" 0 (
      (961.8321 5877.8626) (961.8321 5816.7939)
    ))
    ; P1809 -- see feature_dimensions_mm.csv
    ("05_STONE_JOINTS" 0 (
      (961.8321 3709.9237) (961.8321 3740.458) (961.8321 3786.2595)
    ))
    ; P1810 -- see feature_dimensions_mm.csv
    ("05_STONE_JOINTS" 0 (
      (961.8321 3633.5878) (961.8321 3664.1221) (961.8321 3679.3893) (961.8321 3709.9237)
    ))
    ; P1811 -- see feature_dimensions_mm.csv
    ("05_STONE_JOINTS" 0 (
      (961.8321 3190.8397) (961.8321 3114.5038)
    ))
    ; P1812 -- see feature_dimensions_mm.csv
    ("05_STONE_JOINTS" 0 (
      (961.8321 3114.5038) (961.8321 3038.1679)
    ))
    ; P1813 -- see feature_dimensions_mm.csv
    ("05_STONE_JOINTS" 0 (
      (961.8321 3038.1679) (961.8321 2961.8321)
    ))
    ; P1814 -- see feature_dimensions_mm.csv
    ("05_STONE_JOINTS" 0 (
      (961.8321 2961.8321) (1938.9313 2961.8321) (1938.9313 3099.2366) (2061.0687 3099.2366) (2061.0687 2961.8321)
      (2229.0076 2961.8321) (2229.0076 3099.2366) (2351.145 3099.2366) (2351.145 2961.8321) (2519.084 2961.8321)
    ))
    ; P1815 -- see feature_dimensions_mm.csv
    ("05_STONE_JOINTS" 0 (
      (961.8321 2961.8321) (961.8321 2946.5649)
    ))
    ; P1816 -- see feature_dimensions_mm.csv
    ("05_STONE_JOINTS" 0 (
      (961.8321 2946.5649) (961.8321 2854.9618)
    ))
    ; P1817 -- see feature_dimensions_mm.csv
    ("05_STONE_JOINTS" 0 (
      (961.8321 2854.9618) (961.8321 2641.2214)
    ))
    ; P1818 -- see feature_dimensions_mm.csv
    ("05_STONE_JOINTS" 0 (
      (961.8321 2641.2214) (4992.3664 2641.2214)
    ))
    ; P1819 -- see feature_dimensions_mm.csv
    ("05_STONE_JOINTS" 0 (
      (961.8321 2641.2214) (961.8321 2519.084)
    ))
    ; P1820 -- see feature_dimensions_mm.csv
    ("05_STONE_JOINTS" 0 (
      (961.8321 2519.084) (961.8321 2442.7481)
    ))
    ; P1821 -- see feature_dimensions_mm.csv
    ("05_STONE_JOINTS" 0 (
      (961.8321 2442.7481) (961.8321 2366.4122)
    ))
    ; P1822 -- see feature_dimensions_mm.csv
    ("05_STONE_JOINTS" 0 (
      (961.8321 2366.4122) (961.8321 2305.3435)
    ))
    ; P1823 -- see feature_dimensions_mm.csv
    ("05_STONE_JOINTS" 0 (
      (961.8321 2305.3435) (1863.4351 2305.3435)
    ))
    ; P1824 -- see feature_dimensions_mm.csv
    ("05_STONE_JOINTS" 0 (
      (961.8321 2305.3435) (961.8321 2274.8092)
    ))
    ; P1825 -- see feature_dimensions_mm.csv
    ("05_STONE_JOINTS" 0 (
      (961.8321 2274.8092) (961.8321 2183.2061)
    ))
    ; P1826 -- see feature_dimensions_mm.csv
    ("05_STONE_JOINTS" 0 (
      (961.8321 2183.2061) (961.8321 1984.7328)
    ))
    ; P1827 -- see feature_dimensions_mm.csv
    ("05_STONE_JOINTS" 0 (
      (961.8321 1984.7328) (1325.6947 1984.7328)
    ))
    ; P1828 -- see feature_dimensions_mm.csv
    ("05_STONE_JOINTS" 0 (
      (961.8321 1984.7328) (961.8321 1847.3282)
    ))
    ; P1829 -- see feature_dimensions_mm.csv
    ("05_STONE_JOINTS" 0 (
      (961.8321 1847.3282) (961.8321 1770.9924)
    ))
    ; P1830 -- see feature_dimensions_mm.csv
    ("05_STONE_JOINTS" 0 (
      (961.8321 1770.9924) (961.8321 1694.6565)
    ))
    ; P1831 -- see feature_dimensions_mm.csv
    ("05_STONE_JOINTS" 0 (
      (961.8321 1694.6565) (961.8321 1633.5878)
    ))
    ; P1832 -- see feature_dimensions_mm.csv
    ("05_STONE_JOINTS" 0 (
      (961.8321 1633.5878) (1435.1145 1633.5878)
    ))
    ; P1833 -- see feature_dimensions_mm.csv
    ("05_STONE_JOINTS" 0 (
      (961.8321 1633.5878) (961.8321 1603.0534)
    ))
    ; P1834 -- see feature_dimensions_mm.csv
    ("05_STONE_JOINTS" 0 (
      (961.8321 1603.0534) (961.8321 1511.4504)
    ))
    ; P1835 -- see feature_dimensions_mm.csv
    ("05_STONE_JOINTS" 0 (
      (961.8321 1511.4504) (961.8321 1282.4427)
    ))
    ; P1836 -- see feature_dimensions_mm.csv
    ("05_STONE_JOINTS" 0 (
      (961.8321 1282.4427) (1435.1145 1282.4427) (1435.1145 1633.5878)
    ))
    ; P1837 -- see feature_dimensions_mm.csv
    ("05_STONE_JOINTS" 0 (
      (961.8321 1282.4427) (961.8321 1175.5725)
    ))
    ; P1838 -- see feature_dimensions_mm.csv
    ("05_STONE_JOINTS" 0 (
      (961.8321 1175.5725) (961.8321 1099.2366)
    ))
    ; P1839 -- see feature_dimensions_mm.csv
    ("05_STONE_JOINTS" 0 (
      (961.8321 1099.2366) (961.8321 1022.9008)
    ))
    ; P1840 -- see feature_dimensions_mm.csv
    ("05_STONE_JOINTS" 0 (
      (961.8321 1022.9008) (961.8321 931.2977)
    ))
    ; P1841 -- see feature_dimensions_mm.csv
    ("05_STONE_JOINTS" 0 (
      (961.8321 931.2977) (1435.1145 931.2977)
    ))
    ; P1842 -- see feature_dimensions_mm.csv
    ("05_STONE_JOINTS" 0 (
      (961.8321 931.2977) (961.8321 839.6947)
    ))
    ; P1843 -- see feature_dimensions_mm.csv
    ("05_STONE_JOINTS" 0 (
      (961.8321 839.6947) (961.8321 809.1603)
    ))
    ; P1844 -- see feature_dimensions_mm.csv
    ("05_STONE_JOINTS" 0 (
      (961.8321 809.1603) (961.8321 656.4885)
    ))
    ; P1845 -- see feature_dimensions_mm.csv
    ("05_STONE_JOINTS" 0 (
      (961.8321 656.4885) (1435.1145 656.4885)
    ))
    ; P1846 -- see feature_dimensions_mm.csv
    ("05_STONE_JOINTS" 0 (
      (4152.6718 656.4885) (4244.2748 656.4885) (4519.084 656.4885) (4992.3664 656.4885) (4992.3664 0.0)
      (961.8321 0.0) (961.8321 656.4885)
    ))
    ; P1847 -- see feature_dimensions_mm.csv
    ("05_STONE_JOINTS" 0 (
      (1526.7176 9572.5191) (1175.5725 9572.5191)
    ))
    ; P1848 -- see feature_dimensions_mm.csv
    ("05_STONE_JOINTS" 0 (
      (1175.5725 9496.1832) (1175.5725 9557.2519) (1175.5725 9572.5191)
    ))
    ; P1849 -- see feature_dimensions_mm.csv
    ("05_STONE_JOINTS" 0 (
      (1175.5725 9496.1832) (1526.7176 9496.1832)
    ))
    ; P1850 -- see feature_dimensions_mm.csv
    ("05_STONE_JOINTS" 0 (
      (1175.5725 9419.8473) (1175.5725 9496.1832)
    ))
    ; P1851 -- see feature_dimensions_mm.csv
    ("05_STONE_JOINTS" 0 (
      (1175.5725 9419.8473) (1526.7176 9419.8473)
    ))
    ; P1852 -- see feature_dimensions_mm.csv
    ("05_STONE_JOINTS" 0 (
      (1175.5725 9328.2443) (1175.5725 9419.8473)
    ))
    ; P1853 -- see feature_dimensions_mm.csv
    ("05_STONE_JOINTS" 0 (
      (1175.5725 9328.2443) (1526.7176 9328.2443)
    ))
    ; P1854 -- see feature_dimensions_mm.csv
    ("05_STONE_JOINTS" 0 (
      (1175.5725 9236.6412) (1175.5725 9328.2443)
    ))
    ; P1855 -- see feature_dimensions_mm.csv
    ("05_STONE_JOINTS" 0 (
      (1175.5725 9236.6412) (1190.8397 9236.6412)
    ))
    ; P1856 -- see feature_dimensions_mm.csv
    ("05_STONE_JOINTS" 0 (
      (1175.5725 8900.7634) (1190.8397 8900.7634)
    ))
    ; P1857 -- see feature_dimensions_mm.csv
    ("05_STONE_JOINTS" 0 (
      (1175.5725 8824.4275) (1175.5725 8900.7634)
    ))
    ; P1858 -- see feature_dimensions_mm.csv
    ("05_STONE_JOINTS" 0 (
      (1175.5725 8824.4275) (1526.7176 8824.4275)
    ))
    ; P1859 -- see feature_dimensions_mm.csv
    ("05_STONE_JOINTS" 0 (
      (1175.5725 8748.0916) (1175.5725 8824.4275)
    ))
    ; P1860 -- see feature_dimensions_mm.csv
    ("05_STONE_JOINTS" 0 (
      (1175.5725 8748.0916) (1526.7176 8748.0916)
    ))
    ; P1861 -- see feature_dimensions_mm.csv
    ("05_STONE_JOINTS" 0 (
      (1175.5725 8656.4885) (1175.5725 8748.0916)
    ))
    ; P1862 -- see feature_dimensions_mm.csv
    ("05_STONE_JOINTS" 0 (
      (1175.5725 8656.4885) (1526.7176 8656.4885)
    ))
    ; P1863 -- see feature_dimensions_mm.csv
    ("05_STONE_JOINTS" 0 (
      (1175.5725 8564.8855) (1175.5725 8656.4885)
    ))
    ; P1864 -- see feature_dimensions_mm.csv
    ("05_STONE_JOINTS" 0 (
      (1175.5725 8564.8855) (1190.8397 8564.8855)
    ))
    ; P1865 -- see feature_dimensions_mm.csv
    ("05_STONE_JOINTS" 0 (
      (1175.5725 8229.0076) (1190.8397 8229.0076)
    ))
    ; P1866 -- see feature_dimensions_mm.csv
    ("05_STONE_JOINTS" 0 (
      (1175.5725 8152.6718) (1175.5725 8229.0076)
    ))
    ; P1867 -- see feature_dimensions_mm.csv
    ("05_STONE_JOINTS" 0 (
      (1175.5725 8152.6718) (1526.7176 8152.6718)
    ))
    ; P1868 -- see feature_dimensions_mm.csv
    ("05_STONE_JOINTS" 0 (
      (1175.5725 8076.3359) (1175.5725 8152.6718)
    ))
    ; P1869 -- see feature_dimensions_mm.csv
    ("05_STONE_JOINTS" 0 (
      (1175.5725 8076.3359) (1207.771 8076.3359) (1435.4046 8076.3359) (1526.7176 8076.3359)
    ))
    ; P1870 -- see feature_dimensions_mm.csv
    ("05_STONE_JOINTS" 0 (
      (1190.8397 9236.6412) (1206.1069 9236.6412) (1206.1069 9312.9771) (1404.5802 9312.9771) (1404.5802 9236.6412)
      (1511.4504 9236.6412)
    ))
    ; P1871 -- see feature_dimensions_mm.csv
    ("05_STONE_JOINTS" 0 (
      (1190.8397 9160.3053) (1190.8397 9236.6412)
    ))
    ; P1872 -- see feature_dimensions_mm.csv
    ("05_STONE_JOINTS" 0 (
      (1190.8397 9083.9695) (1190.8397 9160.3053)
    ))
    ; P1873 -- see feature_dimensions_mm.csv
    ("05_STONE_JOINTS" 0 (
      (1190.8397 8992.3664) (1190.8397 9083.9695)
    ))
    ; P1874 -- see feature_dimensions_mm.csv
    ("05_STONE_JOINTS" 0 (
      (1190.8397 8900.7634) (1190.8397 8992.3664)
    ))
    ; P1875 -- see feature_dimensions_mm.csv
    ("05_STONE_JOINTS" 0 (
      (1190.8397 8900.7634) (1511.4504 8900.7634)
    ))
    ; P1876 -- see feature_dimensions_mm.csv
    ("05_STONE_JOINTS" 0 (
      (1190.8397 8564.8855) (1511.4504 8564.8855)
    ))
    ; P1877 -- see feature_dimensions_mm.csv
    ("05_STONE_JOINTS" 0 (
      (1190.8397 8488.5496) (1190.8397 8564.8855)
    ))
    ; P1878 -- see feature_dimensions_mm.csv
    ("05_STONE_JOINTS" 0 (
      (1190.8397 8412.2137) (1190.8397 8488.5496)
    ))
    ; P1879 -- see feature_dimensions_mm.csv
    ("05_STONE_JOINTS" 0 (
      (1190.8397 8320.6107) (1190.8397 8412.2137)
    ))
    ; P1880 -- see feature_dimensions_mm.csv
    ("05_STONE_JOINTS" 0 (
      (1190.8397 8229.0076) (1190.8397 8320.6107)
    ))
    ; P1881 -- see feature_dimensions_mm.csv
    ("05_STONE_JOINTS" 0 (
      (1190.8397 8229.0076) (1511.4504 8229.0076)
    ))
    ; P1882 -- see feature_dimensions_mm.csv
    ("05_STONE_JOINTS" 0 (
      (1325.6947 1984.7328) (1236.6412 2061.0687)
    ))
    ; P1883 -- see feature_dimensions_mm.csv
    ("05_STONE_JOINTS" 0 (
      (1343.5115 1969.4656) (1325.6947 1984.7328)
    ))
    ; P1884 -- see feature_dimensions_mm.csv
    ("05_STONE_JOINTS" 0 (
      (1435.1145 1862.5954) (1435.1145 1633.5878)
    ))
    ; P1885 -- see feature_dimensions_mm.csv
    ("05_STONE_JOINTS" 0 (
      (1511.4504 9236.6412) (1526.7176 9236.6412)
    ))
    ; P1886 -- see feature_dimensions_mm.csv
    ("05_STONE_JOINTS" 0 (
      (1511.4504 9160.3053) (1511.4504 9236.6412)
    ))
    ; P1887 -- see feature_dimensions_mm.csv
    ("05_STONE_JOINTS" 0 (
      (1511.4504 9160.3053) (1694.6565 9160.3053) (1694.6565 9236.6412)
    ))
    ; P1888 -- see feature_dimensions_mm.csv
    ("05_STONE_JOINTS" 0 (
      (1511.4504 9083.9695) (1511.4504 9160.3053)
    ))
    ; P1889 -- see feature_dimensions_mm.csv
    ("05_STONE_JOINTS" 0 (
      (1511.4504 9083.9695) (1694.6565 9083.9695)
    ))
    ; P1890 -- see feature_dimensions_mm.csv
    ("05_STONE_JOINTS" 0 (
      (1511.4504 8992.3664) (1511.4504 9083.9695)
    ))
    ; P1891 -- see feature_dimensions_mm.csv
    ("05_STONE_JOINTS" 0 (
      (1511.4504 8992.3664) (1694.6565 8992.3664)
    ))
    ; P1892 -- see feature_dimensions_mm.csv
    ("05_STONE_JOINTS" 0 (
      (1511.4504 8900.7634) (1511.4504 8992.3664)
    ))
    ; P1893 -- see feature_dimensions_mm.csv
    ("05_STONE_JOINTS" 0 (
      (1511.4504 8900.7634) (1526.7176 8900.7634)
    ))
    ; P1894 -- see feature_dimensions_mm.csv
    ("05_STONE_JOINTS" 0 (
      (1511.4504 8564.8855) (1526.7176 8564.8855)
    ))
    ; P1895 -- see feature_dimensions_mm.csv
    ("05_STONE_JOINTS" 0 (
      (1511.4504 8488.5496) (1511.4504 8564.8855)
    ))
    ; P1896 -- see feature_dimensions_mm.csv
    ("05_STONE_JOINTS" 0 (
      (1511.4504 8488.5496) (1862.5954 8488.5496)
    ))
    ; P1897 -- see feature_dimensions_mm.csv
    ("05_STONE_JOINTS" 0 (
      (1511.4504 8412.2137) (1511.4504 8488.5496)
    ))
    ; P1898 -- see feature_dimensions_mm.csv
    ("05_STONE_JOINTS" 0 (
      (1511.4504 8412.2137) (1862.5954 8412.2137)
    ))
    ; P1899 -- see feature_dimensions_mm.csv
    ("05_STONE_JOINTS" 0 (
      (1511.4504 8320.6107) (1511.4504 8412.2137)
    ))
    ; P1900 -- see feature_dimensions_mm.csv
    ("05_STONE_JOINTS" 0 (
      (1511.4504 8320.6107) (1862.5954 8320.6107)
    ))
    ; P1901 -- see feature_dimensions_mm.csv
    ("05_STONE_JOINTS" 0 (
      (1511.4504 8229.0076) (1511.4504 8320.6107)
    ))
    ; P1902 -- see feature_dimensions_mm.csv
    ("05_STONE_JOINTS" 0 (
      (1511.4504 8229.0076) (1526.7176 8229.0076)
    ))
    ; P1903 -- see feature_dimensions_mm.csv
    ("05_STONE_JOINTS" 0 (
      (1847.3282 9572.5191) (1526.7176 9572.5191)
    ))
    ; P1904 -- see feature_dimensions_mm.csv
    ("05_STONE_JOINTS" 0 (
      (1526.7176 9496.1832) (1526.7176 9557.2519) (1526.7176 9572.5191)
    ))
    ; P1905 -- see feature_dimensions_mm.csv
    ("05_STONE_JOINTS" 0 (
      (1526.7176 9419.8473) (1526.7176 9496.1832)
    ))
    ; P1906 -- see feature_dimensions_mm.csv
    ("05_STONE_JOINTS" 0 (
      (1526.7176 9328.2443) (1526.7176 9419.8473)
    ))
    ; P1907 -- see feature_dimensions_mm.csv
    ("05_STONE_JOINTS" 0 (
      (1526.7176 9236.6412) (1526.7176 9328.2443)
    ))
    ; P1908 -- see feature_dimensions_mm.csv
    ("05_STONE_JOINTS" 0 (
      (1526.7176 9236.6412) (1694.6565 9236.6412)
    ))
    ; P1909 -- see feature_dimensions_mm.csv
    ("05_STONE_JOINTS" 0 (
      (1526.7176 8900.7634) (1847.3282 8900.7634)
    ))
    ; P1910 -- see feature_dimensions_mm.csv
    ("05_STONE_JOINTS" 0 (
      (1526.7176 8824.4275) (1526.7176 8900.7634)
    ))
    ; P1911 -- see feature_dimensions_mm.csv
    ("05_STONE_JOINTS" 0 (
      (1526.7176 8748.0916) (1526.7176 8824.4275)
    ))
    ; P1912 -- see feature_dimensions_mm.csv
    ("05_STONE_JOINTS" 0 (
      (1526.7176 8656.4885) (1526.7176 8748.0916)
    ))
    ; P1913 -- see feature_dimensions_mm.csv
    ("05_STONE_JOINTS" 0 (
      (1526.7176 8564.8855) (1526.7176 8656.4885)
    ))
    ; P1914 -- see feature_dimensions_mm.csv
    ("05_STONE_JOINTS" 0 (
      (1526.7176 8564.8855) (1847.3282 8564.8855)
    ))
    ; P1915 -- see feature_dimensions_mm.csv
    ("05_STONE_JOINTS" 0 (
      (1526.7176 8229.0076) (1847.3282 8229.0076)
    ))
    ; P1916 -- see feature_dimensions_mm.csv
    ("05_STONE_JOINTS" 0 (
      (1526.7176 8152.6718) (1526.7176 8229.0076)
    ))
    ; P1917 -- see feature_dimensions_mm.csv
    ("05_STONE_JOINTS" 0 (
      (1526.7176 8076.3359) (1526.7176 8152.6718)
    ))
    ; P1918 -- see feature_dimensions_mm.csv
    ("05_STONE_JOINTS" 0 (
      (1526.7176 8076.3359) (1621.6489 8076.3359) (1847.3282 8076.3359) (1847.3282 8152.6718)
    ))
    ; P1919 -- see feature_dimensions_mm.csv
    ("05_STONE_JOINTS" 0 (
      (1694.6565 9236.6412) (1694.6565 9312.9771) (1847.3282 9312.9771)
    ))
    ; P1920 -- see feature_dimensions_mm.csv
    ("05_STONE_JOINTS" 0 (
      (2198.4733 9572.5191) (1847.3282 9572.5191)
    ))
    ; P1921 -- see feature_dimensions_mm.csv
    ("05_STONE_JOINTS" 0 (
      (1847.3282 9496.1832) (1847.3282 9557.2519) (1847.3282 9572.5191)
    ))
    ; P1922 -- see feature_dimensions_mm.csv
    ("05_STONE_JOINTS" 0 (
      (1847.3282 9496.1832) (2198.4733 9496.1832)
    ))
    ; P1923 -- see feature_dimensions_mm.csv
    ("05_STONE_JOINTS" 0 (
      (1847.3282 9419.8473) (1847.3282 9496.1832)
    ))
    ; P1924 -- see feature_dimensions_mm.csv
    ("05_STONE_JOINTS" 0 (
      (1847.3282 9419.8473) (2198.4733 9419.8473)
    ))
    ; P1925 -- see feature_dimensions_mm.csv
    ("05_STONE_JOINTS" 0 (
      (1847.3282 9328.2443) (1847.3282 9419.8473)
    ))
    ; P1926 -- see feature_dimensions_mm.csv
    ("05_STONE_JOINTS" 0 (
      (1847.3282 9328.2443) (2198.4733 9328.2443)
    ))
    ; P1927 -- see feature_dimensions_mm.csv
    ("05_STONE_JOINTS" 0 (
      (1847.3282 9312.9771) (1847.3282 9328.2443)
    ))
    ; P1928 -- see feature_dimensions_mm.csv
    ("05_STONE_JOINTS" 0 (
      (1847.3282 9312.9771) (1893.1298 9312.9771) (1893.1298 9236.6412)
    ))
    ; P1929 -- see feature_dimensions_mm.csv
    ("05_STONE_JOINTS" 0 (
      (1847.3282 8900.7634) (1862.5954 8900.7634)
    ))
    ; P1930 -- see feature_dimensions_mm.csv
    ("05_STONE_JOINTS" 0 (
      (1847.3282 8824.4275) (1847.3282 8900.7634)
    ))
    ; P1931 -- see feature_dimensions_mm.csv
    ("05_STONE_JOINTS" 0 (
      (1847.3282 8824.4275) (2198.4733 8824.4275)
    ))
    ; P1932 -- see feature_dimensions_mm.csv
    ("05_STONE_JOINTS" 0 (
      (1847.3282 8748.0916) (1847.3282 8824.4275)
    ))
    ; P1933 -- see feature_dimensions_mm.csv
    ("05_STONE_JOINTS" 0 (
      (1847.3282 8748.0916) (2198.4733 8748.0916)
    ))
    ; P1934 -- see feature_dimensions_mm.csv
    ("05_STONE_JOINTS" 0 (
      (1847.3282 8656.4885) (1847.3282 8748.0916)
    ))
    ; P1935 -- see feature_dimensions_mm.csv
    ("05_STONE_JOINTS" 0 (
      (1847.3282 8656.4885) (2198.4733 8656.4885)
    ))
    ; P1936 -- see feature_dimensions_mm.csv
    ("05_STONE_JOINTS" 0 (
      (1847.3282 8564.8855) (1847.3282 8656.4885)
    ))
    ; P1937 -- see feature_dimensions_mm.csv
    ("05_STONE_JOINTS" 0 (
      (1847.3282 8564.8855) (1862.5954 8564.8855)
    ))
    ; P1938 -- see feature_dimensions_mm.csv
    ("05_STONE_JOINTS" 0 (
      (1847.3282 8229.0076) (1862.5954 8229.0076)
    ))
    ; P1939 -- see feature_dimensions_mm.csv
    ("05_STONE_JOINTS" 0 (
      (1847.3282 8152.6718) (1847.3282 8229.0076)
    ))
    ; P1940 -- see feature_dimensions_mm.csv
    ("05_STONE_JOINTS" 0 (
      (1847.3282 8152.6718) (2198.4733 8152.6718)
    ))
    ; P1941 -- see feature_dimensions_mm.csv
    ("05_STONE_JOINTS" 0 (
      (1849.2824 8076.3359) (2035.5267 8076.3359)
    ))
    ; P1942 -- see feature_dimensions_mm.csv
    ("05_STONE_JOINTS" 0 (
      (1863.4351 2305.3435) (1856.8855 2300.2901)
    ))
    ; P1943 -- see feature_dimensions_mm.csv
    ("05_STONE_JOINTS" 0 (
      (1862.5954 8900.7634) (2183.2061 8900.7634)
    ))
    ; P1944 -- see feature_dimensions_mm.csv
    ("05_STONE_JOINTS" 0 (
      (1893.1298 9236.6412) (1893.1298 8946.5649) (1862.5954 8946.5649) (1862.5954 8900.7634)
    ))
    ; P1945 -- see feature_dimensions_mm.csv
    ("05_STONE_JOINTS" 0 (
      (1862.5954 8564.8855) (2183.2061 8564.8855)
    ))
    ; P1946 -- see feature_dimensions_mm.csv
    ("05_STONE_JOINTS" 0 (
      (1862.5954 8488.5496) (1862.5954 8564.8855)
    ))
    ; P1947 -- see feature_dimensions_mm.csv
    ("05_STONE_JOINTS" 0 (
      (1862.5954 8412.2137) (1862.5954 8488.5496)
    ))
    ; P1948 -- see feature_dimensions_mm.csv
    ("05_STONE_JOINTS" 0 (
      (1862.5954 8320.6107) (1862.5954 8412.2137)
    ))
    ; P1949 -- see feature_dimensions_mm.csv
    ("05_STONE_JOINTS" 0 (
      (1862.5954 8229.0076) (1862.5954 8320.6107)
    ))
    ; P1950 -- see feature_dimensions_mm.csv
    ("05_STONE_JOINTS" 0 (
      (1862.5954 8229.0076) (2183.2061 8229.0076)
    ))
    ; P1951 -- see feature_dimensions_mm.csv
    ("05_STONE_JOINTS" 0 (
      (1887.7863 2324.1221) (1863.4351 2305.3435)
    ))
    ; P1952 -- see feature_dimensions_mm.csv
    ("05_STONE_JOINTS" 0 (
      (1893.1298 9236.6412) (2183.2061 9236.6412) (2183.2061 9312.9771) (2198.4733 9312.9771)
    ))
    ; P1953 -- see feature_dimensions_mm.csv
    ("05_STONE_JOINTS" 0 (
      (1954.1985 2365.8473) (1920.2595 2346.0)
    ))
    ; P1954 -- see feature_dimensions_mm.csv
    ("05_STONE_JOINTS" 0 (
      (2183.2061 8900.7634) (2198.4733 8900.7634)
    ))
    ; P1955 -- see feature_dimensions_mm.csv
    ("05_STONE_JOINTS" 0 (
      (2183.2061 8900.7634) (2183.2061 8946.5649) (2381.6794 8946.5649) (2381.6794 8992.3664) (2534.3511 8992.3664)
    ))
    ; P1956 -- see feature_dimensions_mm.csv
    ("05_STONE_JOINTS" 0 (
      (2183.2061 8564.8855) (2198.4733 8564.8855)
    ))
    ; P1957 -- see feature_dimensions_mm.csv
    ("05_STONE_JOINTS" 0 (
      (2183.2061 8488.5496) (2183.2061 8564.8855)
    ))
    ; P1958 -- see feature_dimensions_mm.csv
    ("05_STONE_JOINTS" 0 (
      (2183.2061 8488.5496) (2534.3511 8488.5496)
    ))
    ; P1959 -- see feature_dimensions_mm.csv
    ("05_STONE_JOINTS" 0 (
      (2183.2061 8412.2137) (2183.2061 8488.5496)
    ))
    ; P1960 -- see feature_dimensions_mm.csv
    ("05_STONE_JOINTS" 0 (
      (2183.2061 8412.2137) (2534.3511 8412.2137)
    ))
    ; P1961 -- see feature_dimensions_mm.csv
    ("05_STONE_JOINTS" 0 (
      (2183.2061 8320.6107) (2183.2061 8412.2137)
    ))
    ; P1962 -- see feature_dimensions_mm.csv
    ("05_STONE_JOINTS" 0 (
      (2183.2061 8320.6107) (2534.3511 8320.6107)
    ))
    ; P1963 -- see feature_dimensions_mm.csv
    ("05_STONE_JOINTS" 0 (
      (2183.2061 8229.0076) (2183.2061 8320.6107)
    ))
    ; P1964 -- see feature_dimensions_mm.csv
    ("05_STONE_JOINTS" 0 (
      (2183.2061 8229.0076) (2198.4733 8229.0076)
    ))
    ; P1965 -- see feature_dimensions_mm.csv
    ("05_STONE_JOINTS" 0 (
      (2519.084 9572.5191) (2198.4733 9572.5191)
    ))
    ; P1966 -- see feature_dimensions_mm.csv
    ("05_STONE_JOINTS" 0 (
      (2198.4733 9496.1832) (2198.4733 9557.2519) (2198.4733 9572.5191)
    ))
    ; P1967 -- see feature_dimensions_mm.csv
    ("05_STONE_JOINTS" 0 (
      (2198.4733 9419.8473) (2198.4733 9496.1832)
    ))
    ; P1968 -- see feature_dimensions_mm.csv
    ("05_STONE_JOINTS" 0 (
      (2198.4733 9328.2443) (2198.4733 9419.8473)
    ))
    ; P1969 -- see feature_dimensions_mm.csv
    ("05_STONE_JOINTS" 0 (
      (2198.4733 9312.9771) (2198.4733 9328.2443)
    ))
    ; P1970 -- see feature_dimensions_mm.csv
    ("05_STONE_JOINTS" 0 (
      (2198.4733 9312.9771) (2381.6794 9312.9771) (2381.6794 9236.6412)
    ))
    ; P1971 -- see feature_dimensions_mm.csv
    ("05_STONE_JOINTS" 0 (
      (2198.4733 8900.7634) (2519.084 8900.7634)
    ))
    ; P1972 -- see feature_dimensions_mm.csv
    ("05_STONE_JOINTS" 0 (
      (2198.4733 8824.4275) (2198.4733 8900.7634)
    ))
    ; P1973 -- see feature_dimensions_mm.csv
    ("05_STONE_JOINTS" 0 (
      (2198.4733 8748.0916) (2198.4733 8824.4275)
    ))
    ; P1974 -- see feature_dimensions_mm.csv
    ("05_STONE_JOINTS" 0 (
      (2198.4733 8656.4885) (2198.4733 8748.0916)
    ))
    ; P1975 -- see feature_dimensions_mm.csv
    ("05_STONE_JOINTS" 0 (
      (2198.4733 8564.8855) (2198.4733 8656.4885)
    ))
    ; P1976 -- see feature_dimensions_mm.csv
    ("05_STONE_JOINTS" 0 (
      (2198.4733 8564.8855) (2519.084 8564.8855)
    ))
    ; P1977 -- see feature_dimensions_mm.csv
    ("05_STONE_JOINTS" 0 (
      (2198.4733 8229.0076) (2519.084 8229.0076)
    ))
    ; P1978 -- see feature_dimensions_mm.csv
    ("05_STONE_JOINTS" 0 (
      (2198.4733 8152.6718) (2198.4733 8229.0076)
    ))
    ; P1979 -- see feature_dimensions_mm.csv
    ("05_STONE_JOINTS" 0 (
      (2198.4733 8076.3359) (2198.4733 8152.6718)
    ))
    ; P1980 -- see feature_dimensions_mm.csv
    ("05_STONE_JOINTS" 0 (
      (2263.1603 8076.3359) (2449.4046 8076.3359)
    ))
    ; P1981 -- see feature_dimensions_mm.csv
    ("05_STONE_JOINTS" 0 (
      (2381.6794 9236.6412) (2519.084 9236.6412)
    ))
    ; P1982 -- see feature_dimensions_mm.csv
    ("05_STONE_JOINTS" 0 (
      (2381.6794 9236.6412) (2381.6794 9160.3053) (2534.3511 9160.3053)
    ))
    ; P1983 -- see feature_dimensions_mm.csv
    ("05_STONE_JOINTS" 0 (
      (2381.6794 9083.9695) (2534.3511 9083.9695)
    ))
    ; P1984 -- see feature_dimensions_mm.csv
    ("05_STONE_JOINTS" 0 (
      (2870.229 9572.5191) (2519.084 9572.5191)
    ))
    ; P1985 -- see feature_dimensions_mm.csv
    ("05_STONE_JOINTS" 0 (
      (2519.084 9496.1832) (2519.084 9557.2519) (2519.084 9572.5191)
    ))
    ; P1986 -- see feature_dimensions_mm.csv
    ("05_STONE_JOINTS" 0 (
      (2519.084 9496.1832) (2870.229 9496.1832)
    ))
    ; P1987 -- see feature_dimensions_mm.csv
    ("05_STONE_JOINTS" 0 (
      (2519.084 9419.8473) (2519.084 9496.1832)
    ))
    ; P1988 -- see feature_dimensions_mm.csv
    ("05_STONE_JOINTS" 0 (
      (2519.084 9419.8473) (2870.229 9419.8473)
    ))
    ; P1989 -- see feature_dimensions_mm.csv
    ("05_STONE_JOINTS" 0 (
      (2519.084 9328.2443) (2519.084 9419.8473)
    ))
    ; P1990 -- see feature_dimensions_mm.csv
    ("05_STONE_JOINTS" 0 (
      (2519.084 9328.2443) (2870.229 9328.2443)
    ))
    ; P1991 -- see feature_dimensions_mm.csv
    ("05_STONE_JOINTS" 0 (
      (2519.084 9236.6412) (2519.084 9328.2443)
    ))
    ; P1992 -- see feature_dimensions_mm.csv
    ("05_STONE_JOINTS" 0 (
      (2519.084 9236.6412) (2534.3511 9236.6412)
    ))
    ; P1993 -- see feature_dimensions_mm.csv
    ("05_STONE_JOINTS" 0 (
      (2519.084 8900.7634) (2534.3511 8900.7634)
    ))
    ; P1994 -- see feature_dimensions_mm.csv
    ("05_STONE_JOINTS" 0 (
      (2519.084 8824.4275) (2519.084 8900.7634)
    ))
    ; P1995 -- see feature_dimensions_mm.csv
    ("05_STONE_JOINTS" 0 (
      (2519.084 8824.4275) (2870.229 8824.4275)
    ))
    ; P1996 -- see feature_dimensions_mm.csv
    ("05_STONE_JOINTS" 0 (
      (2519.084 8748.0916) (2519.084 8824.4275)
    ))
    ; P1997 -- see feature_dimensions_mm.csv
    ("05_STONE_JOINTS" 0 (
      (2519.084 8748.0916) (2870.229 8748.0916)
    ))
    ; P1998 -- see feature_dimensions_mm.csv
    ("05_STONE_JOINTS" 0 (
      (2519.084 8656.4885) (2519.084 8748.0916)
    ))
    ; P1999 -- see feature_dimensions_mm.csv
    ("05_STONE_JOINTS" 0 (
      (2519.084 8656.4885) (2870.229 8656.4885)
    ))
    ; P2000 -- see feature_dimensions_mm.csv
    ("05_STONE_JOINTS" 0 (
      (2519.084 8564.8855) (2519.084 8656.4885)
    ))
    ; P2001 -- see feature_dimensions_mm.csv
    ("05_STONE_JOINTS" 0 (
      (2519.084 8564.8855) (2534.3511 8564.8855)
    ))
    ; P2002 -- see feature_dimensions_mm.csv
    ("05_STONE_JOINTS" 0 (
      (2519.084 8229.0076) (2534.3511 8229.0076)
    ))
    ; P2003 -- see feature_dimensions_mm.csv
    ("05_STONE_JOINTS" 0 (
      (2519.084 8152.6718) (2519.084 8229.0076)
    ))
    ; P2004 -- see feature_dimensions_mm.csv
    ("05_STONE_JOINTS" 0 (
      (2519.084 8152.6718) (2870.229 8152.6718)
    ))
    ; P2005 -- see feature_dimensions_mm.csv
    ("05_STONE_JOINTS" 0 (
      (2519.084 8076.3359) (2519.084 8152.6718)
    ))
    ; P2006 -- see feature_dimensions_mm.csv
    ("05_STONE_JOINTS" 0 (
      (2534.3511 9236.6412) (2671.7557 9236.6412) (2671.7557 9312.9771) (2870.229 9312.9771)
    ))
    ; P2007 -- see feature_dimensions_mm.csv
    ("05_STONE_JOINTS" 0 (
      (2534.3511 9160.3053) (2534.3511 9236.6412)
    ))
    ; P2008 -- see feature_dimensions_mm.csv
    ("05_STONE_JOINTS" 0 (
      (2534.3511 9083.9695) (2534.3511 9160.3053)
    ))
    ; P2009 -- see feature_dimensions_mm.csv
    ("05_STONE_JOINTS" 0 (
      (2534.3511 8992.3664) (2534.3511 9083.9695)
    ))
    ; P2010 -- see feature_dimensions_mm.csv
    ("05_STONE_JOINTS" 0 (
      (2534.3511 8900.7634) (2534.3511 8992.3664)
    ))
    ; P2011 -- see feature_dimensions_mm.csv
    ("05_STONE_JOINTS" 0 (
      (2534.3511 8900.7634) (2854.9618 8900.7634)
    ))
    ; P2012 -- see feature_dimensions_mm.csv
    ("05_STONE_JOINTS" 0 (
      (2534.3511 8564.8855) (2854.9618 8564.8855)
    ))
    ; P2013 -- see feature_dimensions_mm.csv
    ("05_STONE_JOINTS" 0 (
      (2534.3511 8488.5496) (2534.3511 8564.8855)
    ))
    ; P2014 -- see feature_dimensions_mm.csv
    ("05_STONE_JOINTS" 0 (
      (2534.3511 8412.2137) (2534.3511 8488.5496)
    ))
    ; P2015 -- see feature_dimensions_mm.csv
    ("05_STONE_JOINTS" 0 (
      (2534.3511 8320.6107) (2534.3511 8412.2137)
    ))
    ; P2016 -- see feature_dimensions_mm.csv
    ("05_STONE_JOINTS" 0 (
      (2534.3511 8229.0076) (2534.3511 8320.6107)
    ))
    ; P2017 -- see feature_dimensions_mm.csv
    ("05_STONE_JOINTS" 0 (
      (2534.3511 8229.0076) (2854.9618 8229.0076)
    ))
    ; P2018 -- see feature_dimensions_mm.csv
    ("05_STONE_JOINTS" 0 (
      (2655.6489 2305.3435) (2631.2977 2324.1221)
    ))
    ; P2019 -- see feature_dimensions_mm.csv
    ("05_STONE_JOINTS" 0 (
      (2641.2214 2961.8321) (3343.5115 2961.8321)
    ))
    ; P2020 -- see feature_dimensions_mm.csv
    ("05_STONE_JOINTS" 0 (
      (2655.6489 2305.3435) (3314.6718 2305.3435)
    ))
    ; P2021 -- see feature_dimensions_mm.csv
    ("05_STONE_JOINTS" 0 (
      (2662.1985 2300.2901) (2655.6489 2305.3435)
    ))
    ; P2022 -- see feature_dimensions_mm.csv
    ("05_STONE_JOINTS" 0 (
      (2677.0382 8076.3359) (2863.2824 8076.3359)
    ))
    ; P2023 -- see feature_dimensions_mm.csv
    ("05_STONE_JOINTS" 0 (
      (2854.7481 1995.8321) (2857.4962 1984.7328) (2867.6794 1984.7328)
    ))
    ; P2024 -- see feature_dimensions_mm.csv
    ("05_STONE_JOINTS" 0 (
      (2854.9618 8900.7634) (2870.229 8900.7634)
    ))
    ; P2025 -- see feature_dimensions_mm.csv
    ("05_STONE_JOINTS" 0 (
      (2870.229 8992.3664) (2870.229 8946.5649) (2854.9618 8946.5649) (2854.9618 8900.7634)
    ))
    ; P2026 -- see feature_dimensions_mm.csv
    ("05_STONE_JOINTS" 0 (
      (2854.9618 8564.8855) (2870.229 8564.8855)
    ))
    ; P2027 -- see feature_dimensions_mm.csv
    ("05_STONE_JOINTS" 0 (
      (2854.9618 8488.5496) (2854.9618 8564.8855)
    ))
    ; P2028 -- see feature_dimensions_mm.csv
    ("05_STONE_JOINTS" 0 (
      (2854.9618 8488.5496) (3206.1069 8488.5496)
    ))
    ; P2029 -- see feature_dimensions_mm.csv
    ("05_STONE_JOINTS" 0 (
      (2854.9618 8412.2137) (2854.9618 8488.5496)
    ))
    ; P2030 -- see feature_dimensions_mm.csv
    ("05_STONE_JOINTS" 0 (
      (2854.9618 8412.2137) (3206.1069 8412.2137)
    ))
    ; P2031 -- see feature_dimensions_mm.csv
    ("05_STONE_JOINTS" 0 (
      (2854.9618 8320.6107) (2854.9618 8412.2137)
    ))
    ; P2032 -- see feature_dimensions_mm.csv
    ("05_STONE_JOINTS" 0 (
      (2854.9618 8320.6107) (3206.1069 8320.6107)
    ))
    ; P2033 -- see feature_dimensions_mm.csv
    ("05_STONE_JOINTS" 0 (
      (2854.9618 8229.0076) (2854.9618 8320.6107)
    ))
    ; P2034 -- see feature_dimensions_mm.csv
    ("05_STONE_JOINTS" 0 (
      (2854.9618 8229.0076) (2870.229 8229.0076)
    ))
    ; P2035 -- see feature_dimensions_mm.csv
    ("05_STONE_JOINTS" 0 (
      (2867.6794 1984.7328) (2861.2061 1990.2748)
    ))
    ; P2036 -- see feature_dimensions_mm.csv
    ("05_STONE_JOINTS" 0 (
      (2885.4962 1969.4656) (2867.6794 1984.7328)
    ))
    ; P2037 -- see feature_dimensions_mm.csv
    ("05_STONE_JOINTS" 0 (
      (3190.8397 9572.5191) (2870.229 9572.5191)
    ))
    ; P2038 -- see feature_dimensions_mm.csv
    ("05_STONE_JOINTS" 0 (
      (2870.229 9496.1832) (2870.229 9557.2519) (2870.229 9572.5191)
    ))
    ; P2039 -- see feature_dimensions_mm.csv
    ("05_STONE_JOINTS" 0 (
      (2870.229 9419.8473) (2870.229 9496.1832)
    ))
    ; P2040 -- see feature_dimensions_mm.csv
    ("05_STONE_JOINTS" 0 (
      (2870.229 9328.2443) (2870.229 9419.8473)
    ))
    ; P2041 -- see feature_dimensions_mm.csv
    ("05_STONE_JOINTS" 0 (
      (2870.229 9312.9771) (2870.229 9328.2443)
    ))
    ; P2042 -- see feature_dimensions_mm.csv
    ("05_STONE_JOINTS" 0 (
      (2870.229 9312.9771) (2870.229 9236.6412)
    ))
    ; P2043 -- see feature_dimensions_mm.csv
    ("05_STONE_JOINTS" 0 (
      (2870.229 9236.6412) (3160.3053 9236.6412)
    ))
    ; P2044 -- see feature_dimensions_mm.csv
    ("05_STONE_JOINTS" 0 (
      (2870.229 9236.6412) (2870.229 9160.3053)
    ))
    ; P2045 -- see feature_dimensions_mm.csv
    ("05_STONE_JOINTS" 0 (
      (2870.229 9160.3053) (3160.3053 9160.3053)
    ))
    ; P2046 -- see feature_dimensions_mm.csv
    ("05_STONE_JOINTS" 0 (
      (2870.229 9160.3053) (2870.229 9083.9695)
    ))
    ; P2047 -- see feature_dimensions_mm.csv
    ("05_STONE_JOINTS" 0 (
      (2870.229 9083.9695) (3160.3053 9083.9695)
    ))
    ; P2048 -- see feature_dimensions_mm.csv
    ("05_STONE_JOINTS" 0 (
      (2870.229 9083.9695) (2870.229 8992.3664)
    ))
    ; P2049 -- see feature_dimensions_mm.csv
    ("05_STONE_JOINTS" 0 (
      (2870.229 8992.3664) (3160.3053 8992.3664)
    ))
    ; P2050 -- see feature_dimensions_mm.csv
    ("05_STONE_JOINTS" 0 (
      (2870.229 8900.7634) (3190.8397 8900.7634)
    ))
    ; P2051 -- see feature_dimensions_mm.csv
    ("05_STONE_JOINTS" 0 (
      (2870.229 8824.4275) (2870.229 8900.7634)
    ))
    ; P2052 -- see feature_dimensions_mm.csv
    ("05_STONE_JOINTS" 0 (
      (2870.229 8748.0916) (2870.229 8824.4275)
    ))
    ; P2053 -- see feature_dimensions_mm.csv
    ("05_STONE_JOINTS" 0 (
      (2870.229 8656.4885) (2870.229 8748.0916)
    ))
    ; P2054 -- see feature_dimensions_mm.csv
    ("05_STONE_JOINTS" 0 (
      (2870.229 8564.8855) (2870.229 8656.4885)
    ))
    ; P2055 -- see feature_dimensions_mm.csv
    ("05_STONE_JOINTS" 0 (
      (2870.229 8564.8855) (3190.8397 8564.8855)
    ))
    ; P2056 -- see feature_dimensions_mm.csv
    ("05_STONE_JOINTS" 0 (
      (2870.229 8229.0076) (3190.8397 8229.0076)
    ))
    ; P2057 -- see feature_dimensions_mm.csv
    ("05_STONE_JOINTS" 0 (
      (2870.229 8152.6718) (2870.229 8229.0076)
    ))
    ; P2058 -- see feature_dimensions_mm.csv
    ("05_STONE_JOINTS" 0 (
      (2870.229 8152.6718) (2870.229 8076.3359) (3090.916 8076.3359) (3190.8397 8076.3359)
    ))
    ; P2059 -- see feature_dimensions_mm.csv
    ("05_STONE_JOINTS" 0 (
      (3127.2214 1984.7328) (3114.5038 1969.4656)
    ))
    ; P2060 -- see feature_dimensions_mm.csv
    ("05_STONE_JOINTS" 0 (
      (3221.374 1633.5878) (3129.771 1633.5878) (3129.771 1862.5954) (3114.5038 1862.5954)
    ))
    ; P2061 -- see feature_dimensions_mm.csv
    ("05_STONE_JOINTS" 0 (
      (3127.2214 1984.7328) (3221.374 1984.7328)
    ))
    ; P2062 -- see feature_dimensions_mm.csv
    ("05_STONE_JOINTS" 0 (
      (3190.8397 2061.0687) (3127.2214 1984.7328)
    ))
    ; P2063 -- see feature_dimensions_mm.csv
    ("05_STONE_JOINTS" 0 (
      (3129.771 1282.4427) (3221.374 1282.4427)
    ))
    ; P2064 -- see feature_dimensions_mm.csv
    ("05_STONE_JOINTS" 0 (
      (3129.771 931.2977) (3221.374 931.2977)
    ))
    ; P2065 -- see feature_dimensions_mm.csv
    ("05_STONE_JOINTS" 0 (
      (3129.771 656.4885) (3221.374 656.4885)
    ))
    ; P2066 -- see feature_dimensions_mm.csv
    ("05_STONE_JOINTS" 0 (
      (3160.3053 9160.3053) (3160.3053 9236.6412)
    ))
    ; P2067 -- see feature_dimensions_mm.csv
    ("05_STONE_JOINTS" 0 (
      (3160.3053 9236.6412) (3160.3053 9312.9771) (3190.8397 9312.9771)
    ))
    ; P2068 -- see feature_dimensions_mm.csv
    ("05_STONE_JOINTS" 0 (
      (3160.3053 9083.9695) (3160.3053 9160.3053)
    ))
    ; P2069 -- see feature_dimensions_mm.csv
    ("05_STONE_JOINTS" 0 (
      (3160.3053 8992.3664) (3160.3053 9083.9695)
    ))
    ; P2070 -- see feature_dimensions_mm.csv
    ("05_STONE_JOINTS" 0 (
      (3206.1069 8900.7634) (3206.1069 8946.5649) (3160.3053 8946.5649) (3160.3053 8992.3664)
    ))
    ; P2071 -- see feature_dimensions_mm.csv
    ("05_STONE_JOINTS" 0 (
      (3541.9847 9572.5191) (3190.8397 9572.5191)
    ))
    ; P2072 -- see feature_dimensions_mm.csv
    ("05_STONE_JOINTS" 0 (
      (3190.8397 9496.1832) (3190.8397 9557.2519) (3190.8397 9572.5191)
    ))
    ; P2073 -- see feature_dimensions_mm.csv
    ("05_STONE_JOINTS" 0 (
      (3190.8397 9496.1832) (3541.9847 9496.1832)
    ))
    ; P2074 -- see feature_dimensions_mm.csv
    ("05_STONE_JOINTS" 0 (
      (3190.8397 9419.8473) (3190.8397 9496.1832)
    ))
    ; P2075 -- see feature_dimensions_mm.csv
    ("05_STONE_JOINTS" 0 (
      (3190.8397 9419.8473) (3541.9847 9419.8473)
    ))
    ; P2076 -- see feature_dimensions_mm.csv
    ("05_STONE_JOINTS" 0 (
      (3190.8397 9328.2443) (3190.8397 9419.8473)
    ))
    ; P2077 -- see feature_dimensions_mm.csv
    ("05_STONE_JOINTS" 0 (
      (3190.8397 9328.2443) (3541.9847 9328.2443)
    ))
    ; P2078 -- see feature_dimensions_mm.csv
    ("05_STONE_JOINTS" 0 (
      (3190.8397 9312.9771) (3190.8397 9328.2443)
    ))
    ; P2079 -- see feature_dimensions_mm.csv
    ("05_STONE_JOINTS" 0 (
      (3190.8397 9312.9771) (3358.7786 9312.9771) (3358.7786 9236.6412) (3526.7176 9236.6412)
    ))
    ; P2080 -- see feature_dimensions_mm.csv
    ("05_STONE_JOINTS" 0 (
      (3190.8397 8900.7634) (3206.1069 8900.7634)
    ))
    ; P2081 -- see feature_dimensions_mm.csv
    ("05_STONE_JOINTS" 0 (
      (3190.8397 8824.4275) (3190.8397 8900.7634)
    ))
    ; P2082 -- see feature_dimensions_mm.csv
    ("05_STONE_JOINTS" 0 (
      (3190.8397 8824.4275) (3541.9847 8824.4275)
    ))
    ; P2083 -- see feature_dimensions_mm.csv
    ("05_STONE_JOINTS" 0 (
      (3190.8397 8748.0916) (3190.8397 8824.4275)
    ))
    ; P2084 -- see feature_dimensions_mm.csv
    ("05_STONE_JOINTS" 0 (
      (3190.8397 8748.0916) (3541.9847 8748.0916)
    ))
    ; P2085 -- see feature_dimensions_mm.csv
    ("05_STONE_JOINTS" 0 (
      (3190.8397 8656.4885) (3190.8397 8748.0916)
    ))
    ; P2086 -- see feature_dimensions_mm.csv
    ("05_STONE_JOINTS" 0 (
      (3190.8397 8656.4885) (3541.9847 8656.4885)
    ))
    ; P2087 -- see feature_dimensions_mm.csv
    ("05_STONE_JOINTS" 0 (
      (3190.8397 8564.8855) (3190.8397 8656.4885)
    ))
    ; P2088 -- see feature_dimensions_mm.csv
    ("05_STONE_JOINTS" 0 (
      (3190.8397 8564.8855) (3206.1069 8564.8855)
    ))
    ; P2089 -- see feature_dimensions_mm.csv
    ("05_STONE_JOINTS" 0 (
      (3190.8397 8229.0076) (3206.1069 8229.0076)
    ))
    ; P2090 -- see feature_dimensions_mm.csv
    ("05_STONE_JOINTS" 0 (
      (3190.8397 8152.6718) (3190.8397 8229.0076)
    ))
    ; P2091 -- see feature_dimensions_mm.csv
    ("05_STONE_JOINTS" 0 (
      (3190.8397 8152.6718) (3541.9847 8152.6718)
    ))
    ; P2092 -- see feature_dimensions_mm.csv
    ("05_STONE_JOINTS" 0 (
      (3190.8397 8076.3359) (3190.8397 8152.6718)
    ))
    ; P2093 -- see feature_dimensions_mm.csv
    ("05_STONE_JOINTS" 0 (
      (3190.8397 8076.3359) (3277.1603 8076.3359)
    ))
    ; P2094 -- see feature_dimensions_mm.csv
    ("05_STONE_JOINTS" 0 (
      (3206.1069 8900.7634) (3526.7176 8900.7634)
    ))
    ; P2095 -- see feature_dimensions_mm.csv
    ("05_STONE_JOINTS" 0 (
      (3206.1069 8564.8855) (3526.7176 8564.8855)
    ))
    ; P2096 -- see feature_dimensions_mm.csv
    ("05_STONE_JOINTS" 0 (
      (3206.1069 8488.5496) (3206.1069 8564.8855)
    ))
    ; P2097 -- see feature_dimensions_mm.csv
    ("05_STONE_JOINTS" 0 (
      (3206.1069 8412.2137) (3206.1069 8488.5496)
    ))
    ; P2098 -- see feature_dimensions_mm.csv
    ("05_STONE_JOINTS" 0 (
      (3206.1069 8320.6107) (3206.1069 8412.2137)
    ))
    ; P2099 -- see feature_dimensions_mm.csv
    ("05_STONE_JOINTS" 0 (
      (3206.1069 8229.0076) (3206.1069 8320.6107)
    ))
    ; P2100 -- see feature_dimensions_mm.csv
    ("05_STONE_JOINTS" 0 (
      (3206.1069 8229.0076) (3526.7176 8229.0076)
    ))
    ; P2101 -- see feature_dimensions_mm.csv
    ("05_STONE_JOINTS" 0 (
      (3221.374 442.7481) (4152.6718 442.7481) (4152.6718 656.4885)
    ))
    ; P2102 -- see feature_dimensions_mm.csv
    ("05_STONE_JOINTS" 0 (
      (3314.6718 2305.3435) (3299.8473 2284.9924)
    ))
    ; P2103 -- see feature_dimensions_mm.csv
    ("05_STONE_JOINTS" 0 (
      (3317.6031 2309.3588) (3314.6718 2305.3435)
    ))
    ; P2104 -- see feature_dimensions_mm.csv
    ("05_STONE_JOINTS" 0 (
      (3465.6489 2961.8321) (3633.5878 2961.8321)
    ))
    ; P2105 -- see feature_dimensions_mm.csv
    ("05_STONE_JOINTS" 0 (
      (3504.7939 8076.3359) (3541.9847 8076.3359)
    ))
    ; P2106 -- see feature_dimensions_mm.csv
    ("05_STONE_JOINTS" 0 (
      (3526.7176 9236.6412) (3541.9847 9236.6412)
    ))
    ; P2107 -- see feature_dimensions_mm.csv
    ("05_STONE_JOINTS" 0 (
      (3526.7176 9160.3053) (3526.7176 9236.6412)
    ))
    ; P2108 -- see feature_dimensions_mm.csv
    ("05_STONE_JOINTS" 0 (
      (3526.7176 9160.3053) (3648.855 9160.3053)
    ))
    ; P2109 -- see feature_dimensions_mm.csv
    ("05_STONE_JOINTS" 0 (
      (3526.7176 9083.9695) (3526.7176 9160.3053)
    ))
    ; P2110 -- see feature_dimensions_mm.csv
    ("05_STONE_JOINTS" 0 (
      (3526.7176 9083.9695) (3648.855 9083.9695)
    ))
    ; P2111 -- see feature_dimensions_mm.csv
    ("05_STONE_JOINTS" 0 (
      (3526.7176 8992.3664) (3526.7176 9083.9695)
    ))
    ; P2112 -- see feature_dimensions_mm.csv
    ("05_STONE_JOINTS" 0 (
      (3526.7176 8992.3664) (3648.855 8992.3664) (3648.855 9083.9695)
    ))
    ; P2113 -- see feature_dimensions_mm.csv
    ("05_STONE_JOINTS" 0 (
      (3526.7176 8900.7634) (3526.7176 8992.3664)
    ))
    ; P2114 -- see feature_dimensions_mm.csv
    ("05_STONE_JOINTS" 0 (
      (3526.7176 8900.7634) (3541.9847 8900.7634)
    ))
    ; P2115 -- see feature_dimensions_mm.csv
    ("05_STONE_JOINTS" 0 (
      (3526.7176 8564.8855) (3541.9847 8564.8855)
    ))
    ; P2116 -- see feature_dimensions_mm.csv
    ("05_STONE_JOINTS" 0 (
      (3526.7176 8488.5496) (3526.7176 8564.8855)
    ))
    ; P2117 -- see feature_dimensions_mm.csv
    ("05_STONE_JOINTS" 0 (
      (3526.7176 8488.5496) (3877.8626 8488.5496)
    ))
    ; P2118 -- see feature_dimensions_mm.csv
    ("05_STONE_JOINTS" 0 (
      (3526.7176 8412.2137) (3526.7176 8488.5496)
    ))
    ; P2119 -- see feature_dimensions_mm.csv
    ("05_STONE_JOINTS" 0 (
      (3526.7176 8412.2137) (3877.8626 8412.2137)
    ))
    ; P2120 -- see feature_dimensions_mm.csv
    ("05_STONE_JOINTS" 0 (
      (3526.7176 8320.6107) (3526.7176 8412.2137)
    ))
    ; P2121 -- see feature_dimensions_mm.csv
    ("05_STONE_JOINTS" 0 (
      (3526.7176 8320.6107) (3877.8626 8320.6107)
    ))
    ; P2122 -- see feature_dimensions_mm.csv
    ("05_STONE_JOINTS" 0 (
      (3526.7176 8229.0076) (3526.7176 8320.6107)
    ))
    ; P2123 -- see feature_dimensions_mm.csv
    ("05_STONE_JOINTS" 0 (
      (3526.7176 8229.0076) (3541.9847 8229.0076)
    ))
    ; P2124 -- see feature_dimensions_mm.csv
    ("05_STONE_JOINTS" 0 (
      (3862.5954 9572.5191) (3541.9847 9572.5191)
    ))
    ; P2125 -- see feature_dimensions_mm.csv
    ("05_STONE_JOINTS" 0 (
      (3541.9847 9496.1832) (3541.9847 9557.2519) (3541.9847 9572.5191)
    ))
    ; P2126 -- see feature_dimensions_mm.csv
    ("05_STONE_JOINTS" 0 (
      (3541.9847 9419.8473) (3541.9847 9496.1832)
    ))
    ; P2127 -- see feature_dimensions_mm.csv
    ("05_STONE_JOINTS" 0 (
      (3541.9847 9328.2443) (3541.9847 9419.8473)
    ))
    ; P2128 -- see feature_dimensions_mm.csv
    ("05_STONE_JOINTS" 0 (
      (3541.9847 9236.6412) (3541.9847 9328.2443)
    ))
    ; P2129 -- see feature_dimensions_mm.csv
    ("05_STONE_JOINTS" 0 (
      (3541.9847 9236.6412) (3648.855 9236.6412)
    ))
    ; P2130 -- see feature_dimensions_mm.csv
    ("05_STONE_JOINTS" 0 (
      (3541.9847 8900.7634) (3862.5954 8900.7634)
    ))
    ; P2131 -- see feature_dimensions_mm.csv
    ("05_STONE_JOINTS" 0 (
      (3541.9847 8824.4275) (3541.9847 8900.7634)
    ))
    ; P2132 -- see feature_dimensions_mm.csv
    ("05_STONE_JOINTS" 0 (
      (3541.9847 8748.0916) (3541.9847 8824.4275)
    ))
    ; P2133 -- see feature_dimensions_mm.csv
    ("05_STONE_JOINTS" 0 (
      (3541.9847 8656.4885) (3541.9847 8748.0916)
    ))
    ; P2134 -- see feature_dimensions_mm.csv
    ("05_STONE_JOINTS" 0 (
      (3541.9847 8564.8855) (3541.9847 8656.4885)
    ))
    ; P2135 -- see feature_dimensions_mm.csv
    ("05_STONE_JOINTS" 0 (
      (3541.9847 8564.8855) (3862.5954 8564.8855)
    ))
    ; P2136 -- see feature_dimensions_mm.csv
    ("05_STONE_JOINTS" 0 (
      (3541.9847 8229.0076) (3862.5954 8229.0076)
    ))
    ; P2137 -- see feature_dimensions_mm.csv
    ("05_STONE_JOINTS" 0 (
      (3541.9847 8152.6718) (3541.9847 8229.0076)
    ))
    ; P2138 -- see feature_dimensions_mm.csv
    ("05_STONE_JOINTS" 0 (
      (3541.9847 8076.3359) (3541.9847 8152.6718)
    ))
    ; P2139 -- see feature_dimensions_mm.csv
    ("05_STONE_JOINTS" 0 (
      (3541.9847 8076.3359) (3691.0382 8076.3359)
    ))
    ; P2140 -- see feature_dimensions_mm.csv
    ("05_STONE_JOINTS" 0 (
      (3648.855 9236.6412) (3648.855 9312.9771)
    ))
    ; P2141 -- see feature_dimensions_mm.csv
    ("05_STONE_JOINTS" 0 (
      (3648.855 9160.3053) (3648.855 9236.6412)
    ))
    ; P2142 -- see feature_dimensions_mm.csv
    ("05_STONE_JOINTS" 0 (
      (3648.855 9083.9695) (3648.855 9160.3053)
    ))
    ; P2143 -- see feature_dimensions_mm.csv
    ("05_STONE_JOINTS" 0 (
      (3755.7252 2961.8321) (3923.6641 2961.8321)
    ))
    ; P2144 -- see feature_dimensions_mm.csv
    ("05_STONE_JOINTS" 0 (
      (3847.3282 9083.9695) (3877.8626 9083.9695)
    ))
    ; P2145 -- see feature_dimensions_mm.csv
    ("05_STONE_JOINTS" 0 (
      (3847.3282 8992.3664) (3877.8626 8992.3664)
    ))
    ; P2146 -- see feature_dimensions_mm.csv
    ("05_STONE_JOINTS" 0 (
      (4213.7405 9572.5191) (3862.5954 9572.5191)
    ))
    ; P2147 -- see feature_dimensions_mm.csv
    ("05_STONE_JOINTS" 0 (
      (3862.5954 9496.1832) (3862.5954 9557.2519) (3862.5954 9572.5191)
    ))
    ; P2148 -- see feature_dimensions_mm.csv
    ("05_STONE_JOINTS" 0 (
      (3862.5954 9496.1832) (4213.7405 9496.1832)
    ))
    ; P2149 -- see feature_dimensions_mm.csv
    ("05_STONE_JOINTS" 0 (
      (3862.5954 9419.8473) (3862.5954 9496.1832)
    ))
    ; P2150 -- see feature_dimensions_mm.csv
    ("05_STONE_JOINTS" 0 (
      (3862.5954 9419.8473) (4213.7405 9419.8473)
    ))
    ; P2151 -- see feature_dimensions_mm.csv
    ("05_STONE_JOINTS" 0 (
      (3862.5954 9328.2443) (3862.5954 9419.8473)
    ))
    ; P2152 -- see feature_dimensions_mm.csv
    ("05_STONE_JOINTS" 0 (
      (3862.5954 9328.2443) (4213.7405 9328.2443)
    ))
    ; P2153 -- see feature_dimensions_mm.csv
    ("05_STONE_JOINTS" 0 (
      (3862.5954 9236.6412) (3862.5954 9328.2443)
    ))
    ; P2154 -- see feature_dimensions_mm.csv
    ("05_STONE_JOINTS" 0 (
      (3862.5954 9236.6412) (3877.8626 9236.6412)
    ))
    ; P2155 -- see feature_dimensions_mm.csv
    ("05_STONE_JOINTS" 0 (
      (3862.5954 9236.6412) (3847.3282 9236.6412) (3847.3282 9160.3053) (3877.8626 9160.3053)
    ))
    ; P2156 -- see feature_dimensions_mm.csv
    ("05_STONE_JOINTS" 0 (
      (3862.5954 8900.7634) (3877.8626 8900.7634)
    ))
    ; P2157 -- see feature_dimensions_mm.csv
    ("05_STONE_JOINTS" 0 (
      (3862.5954 8824.4275) (3862.5954 8900.7634)
    ))
    ; P2158 -- see feature_dimensions_mm.csv
    ("05_STONE_JOINTS" 0 (
      (3862.5954 8824.4275) (4213.7405 8824.4275)
    ))
    ; P2159 -- see feature_dimensions_mm.csv
    ("05_STONE_JOINTS" 0 (
      (3862.5954 8748.0916) (3862.5954 8824.4275)
    ))
    ; P2160 -- see feature_dimensions_mm.csv
    ("05_STONE_JOINTS" 0 (
      (3862.5954 8748.0916) (4213.7405 8748.0916)
    ))
    ; P2161 -- see feature_dimensions_mm.csv
    ("05_STONE_JOINTS" 0 (
      (3862.5954 8656.4885) (3862.5954 8748.0916)
    ))
    ; P2162 -- see feature_dimensions_mm.csv
    ("05_STONE_JOINTS" 0 (
      (3862.5954 8656.4885) (4213.7405 8656.4885)
    ))
    ; P2163 -- see feature_dimensions_mm.csv
    ("05_STONE_JOINTS" 0 (
      (3862.5954 8564.8855) (3862.5954 8656.4885)
    ))
    ; P2164 -- see feature_dimensions_mm.csv
    ("05_STONE_JOINTS" 0 (
      (3862.5954 8564.8855) (3877.8626 8564.8855)
    ))
    ; P2165 -- see feature_dimensions_mm.csv
    ("05_STONE_JOINTS" 0 (
      (3862.5954 8229.0076) (3877.8626 8229.0076)
    ))
    ; P2166 -- see feature_dimensions_mm.csv
    ("05_STONE_JOINTS" 0 (
      (3862.5954 8152.6718) (3862.5954 8229.0076)
    ))
    ; P2167 -- see feature_dimensions_mm.csv
    ("05_STONE_JOINTS" 0 (
      (3862.5954 8152.6718) (4213.7405 8152.6718)
    ))
    ; P2168 -- see feature_dimensions_mm.csv
    ("05_STONE_JOINTS" 0 (
      (3862.5954 8076.3359) (3862.5954 8152.6718)
    ))
    ; P2169 -- see feature_dimensions_mm.csv
    ("05_STONE_JOINTS" 0 (
      (3877.8626 9236.6412) (4198.4733 9236.6412)
    ))
    ; P2170 -- see feature_dimensions_mm.csv
    ("05_STONE_JOINTS" 0 (
      (3877.8626 9160.3053) (3877.8626 9236.6412)
    ))
    ; P2171 -- see feature_dimensions_mm.csv
    ("05_STONE_JOINTS" 0 (
      (3877.8626 9083.9695) (3877.8626 9160.3053)
    ))
    ; P2172 -- see feature_dimensions_mm.csv
    ("05_STONE_JOINTS" 0 (
      (3877.8626 8992.3664) (3877.8626 9083.9695)
    ))
    ; P2173 -- see feature_dimensions_mm.csv
    ("05_STONE_JOINTS" 0 (
      (3877.8626 8900.7634) (3877.8626 8992.3664)
    ))
    ; P2174 -- see feature_dimensions_mm.csv
    ("05_STONE_JOINTS" 0 (
      (3877.8626 8900.7634) (4198.4733 8900.7634)
    ))
    ; P2175 -- see feature_dimensions_mm.csv
    ("05_STONE_JOINTS" 0 (
      (3877.8626 8564.8855) (4198.4733 8564.8855)
    ))
    ; P2176 -- see feature_dimensions_mm.csv
    ("05_STONE_JOINTS" 0 (
      (3877.8626 8488.5496) (3877.8626 8564.8855)
    ))
    ; P2177 -- see feature_dimensions_mm.csv
    ("05_STONE_JOINTS" 0 (
      (3877.8626 8412.2137) (3877.8626 8488.5496)
    ))
    ; P2178 -- see feature_dimensions_mm.csv
    ("05_STONE_JOINTS" 0 (
      (3877.8626 8320.6107) (3877.8626 8412.2137)
    ))
    ; P2179 -- see feature_dimensions_mm.csv
    ("05_STONE_JOINTS" 0 (
      (3877.8626 8229.0076) (3877.8626 8320.6107)
    ))
    ; P2180 -- see feature_dimensions_mm.csv
    ("05_STONE_JOINTS" 0 (
      (3877.8626 8229.0076) (4198.4733 8229.0076)
    ))
    ; P2181 -- see feature_dimensions_mm.csv
    ("05_STONE_JOINTS" 0 (
      (3918.6718 8076.3359) (4104.916 8076.3359)
    ))
    ; P2182 -- see feature_dimensions_mm.csv
    ("05_STONE_JOINTS" 0 (
      (4045.8015 2961.8321) (4992.3664 2961.8321)
    ))
    ; P2183 -- see feature_dimensions_mm.csv
    ("05_STONE_JOINTS" 0 (
      (4059.374 2305.3435) (4056.4427 2309.3588)
    ))
    ; P2184 -- see feature_dimensions_mm.csv
    ("05_STONE_JOINTS" 0 (
      (4059.374 2305.3435) (4992.3664 2305.3435)
    ))
    ; P2185 -- see feature_dimensions_mm.csv
    ("05_STONE_JOINTS" 0 (
      (4104.6565 2233.1145) (4090.2901 2259.542) (4074.1985 2284.9924) (4059.374 2305.3435)
    ))
    ; P2186 -- see feature_dimensions_mm.csv
    ("05_STONE_JOINTS" 0 (
      (4152.6718 1984.7328) (4152.6718 2030.5344) (4151.6794 2060.4885) (4148.687 2090.3206) (4143.7252 2119.8931)
      (4136.8092 2149.084) (4127.9542 2177.7557) (4117.2214 2205.8015)
    ))
    ; P2187 -- see feature_dimensions_mm.csv
    ("05_STONE_JOINTS" 0 (
      (4152.6718 1984.7328) (4272.2595 1984.7328)
    ))
    ; P2188 -- see feature_dimensions_mm.csv
    ("05_STONE_JOINTS" 0 (
      (4152.6718 1633.5878) (4152.6718 1984.7328)
    ))
    ; P2189 -- see feature_dimensions_mm.csv
    ("05_STONE_JOINTS" 0 (
      (4152.6718 1633.5878) (4244.2748 1633.5878) (4244.2748 1282.4427) (4152.6718 1282.4427)
    ))
    ; P2190 -- see feature_dimensions_mm.csv
    ("05_STONE_JOINTS" 0 (
      (4152.6718 1282.4427) (4152.6718 1633.5878)
    ))
    ; P2191 -- see feature_dimensions_mm.csv
    ("05_STONE_JOINTS" 0 (
      (4152.6718 931.2977) (4152.6718 1282.4427)
    ))
    ; P2192 -- see feature_dimensions_mm.csv
    ("05_STONE_JOINTS" 0 (
      (4152.6718 931.2977) (4244.2748 931.2977)
    ))
    ; P2193 -- see feature_dimensions_mm.csv
    ("05_STONE_JOINTS" 0 (
      (4152.6718 656.4885) (4152.6718 931.2977)
    ))
    ; P2194 -- see feature_dimensions_mm.csv
    ("05_STONE_JOINTS" 0 (
      (4272.2595 1984.7328) (4183.2061 2061.0687)
    ))
    ; P2195 -- see feature_dimensions_mm.csv
    ("05_STONE_JOINTS" 0 (
      (4198.4733 9236.6412) (4213.7405 9236.6412)
    ))
    ; P2196 -- see feature_dimensions_mm.csv
    ("05_STONE_JOINTS" 0 (
      (4198.4733 9160.3053) (4198.4733 9236.6412)
    ))
    ; P2197 -- see feature_dimensions_mm.csv
    ("05_STONE_JOINTS" 0 (
      (4198.4733 9160.3053) (4549.6183 9160.3053)
    ))
    ; P2198 -- see feature_dimensions_mm.csv
    ("05_STONE_JOINTS" 0 (
      (4198.4733 9083.9695) (4198.4733 9160.3053)
    ))
    ; P2199 -- see feature_dimensions_mm.csv
    ("05_STONE_JOINTS" 0 (
      (4198.4733 9083.9695) (4549.6183 9083.9695)
    ))
    ; P2200 -- see feature_dimensions_mm.csv
    ("05_STONE_JOINTS" 0 (
      (4198.4733 8992.3664) (4198.4733 9083.9695)
    ))
    ; P2201 -- see feature_dimensions_mm.csv
    ("05_STONE_JOINTS" 0 (
      (4198.4733 8992.3664) (4549.6183 8992.3664)
    ))
    ; P2202 -- see feature_dimensions_mm.csv
    ("05_STONE_JOINTS" 0 (
      (4198.4733 8900.7634) (4198.4733 8992.3664)
    ))
    ; P2203 -- see feature_dimensions_mm.csv
    ("05_STONE_JOINTS" 0 (
      (4198.4733 8900.7634) (4213.7405 8900.7634)
    ))
    ; P2204 -- see feature_dimensions_mm.csv
    ("05_STONE_JOINTS" 0 (
      (4198.4733 8564.8855) (4213.7405 8564.8855)
    ))
    ; P2205 -- see feature_dimensions_mm.csv
    ("05_STONE_JOINTS" 0 (
      (4198.4733 8488.5496) (4198.4733 8564.8855)
    ))
    ; P2206 -- see feature_dimensions_mm.csv
    ("05_STONE_JOINTS" 0 (
      (4198.4733 8488.5496) (4549.6183 8488.5496)
    ))
    ; P2207 -- see feature_dimensions_mm.csv
    ("05_STONE_JOINTS" 0 (
      (4198.4733 8412.2137) (4198.4733 8488.5496)
    ))
    ; P2208 -- see feature_dimensions_mm.csv
    ("05_STONE_JOINTS" 0 (
      (4198.4733 8412.2137) (4549.6183 8412.2137)
    ))
    ; P2209 -- see feature_dimensions_mm.csv
    ("05_STONE_JOINTS" 0 (
      (4198.4733 8320.6107) (4198.4733 8412.2137)
    ))
    ; P2210 -- see feature_dimensions_mm.csv
    ("05_STONE_JOINTS" 0 (
      (4198.4733 8320.6107) (4549.6183 8320.6107)
    ))
    ; P2211 -- see feature_dimensions_mm.csv
    ("05_STONE_JOINTS" 0 (
      (4198.4733 8229.0076) (4198.4733 8320.6107)
    ))
    ; P2212 -- see feature_dimensions_mm.csv
    ("05_STONE_JOINTS" 0 (
      (4198.4733 8229.0076) (4213.7405 8229.0076)
    ))
    ; P2213 -- see feature_dimensions_mm.csv
    ("05_STONE_JOINTS" 0 (
      (4534.3511 9572.5191) (4213.7405 9572.5191)
    ))
    ; P2214 -- see feature_dimensions_mm.csv
    ("05_STONE_JOINTS" 0 (
      (4213.7405 9496.1832) (4213.7405 9557.2519) (4213.7405 9572.5191)
    ))
    ; P2215 -- see feature_dimensions_mm.csv
    ("05_STONE_JOINTS" 0 (
      (4213.7405 9419.8473) (4213.7405 9496.1832)
    ))
    ; P2216 -- see feature_dimensions_mm.csv
    ("05_STONE_JOINTS" 0 (
      (4213.7405 9328.2443) (4213.7405 9419.8473)
    ))
    ; P2217 -- see feature_dimensions_mm.csv
    ("05_STONE_JOINTS" 0 (
      (4213.7405 9236.6412) (4213.7405 9328.2443)
    ))
    ; P2218 -- see feature_dimensions_mm.csv
    ("05_STONE_JOINTS" 0 (
      (4213.7405 9236.6412) (4534.3511 9236.6412)
    ))
    ; P2219 -- see feature_dimensions_mm.csv
    ("05_STONE_JOINTS" 0 (
      (4213.7405 8900.7634) (4534.3511 8900.7634)
    ))
    ; P2220 -- see feature_dimensions_mm.csv
    ("05_STONE_JOINTS" 0 (
      (4213.7405 8824.4275) (4213.7405 8900.7634)
    ))
    ; P2221 -- see feature_dimensions_mm.csv
    ("05_STONE_JOINTS" 0 (
      (4213.7405 8748.0916) (4213.7405 8824.4275)
    ))
    ; P2222 -- see feature_dimensions_mm.csv
    ("05_STONE_JOINTS" 0 (
      (4213.7405 8656.4885) (4213.7405 8748.0916)
    ))
    ; P2223 -- see feature_dimensions_mm.csv
    ("05_STONE_JOINTS" 0 (
      (4213.7405 8564.8855) (4213.7405 8656.4885)
    ))
    ; P2224 -- see feature_dimensions_mm.csv
    ("05_STONE_JOINTS" 0 (
      (4213.7405 8564.8855) (4534.3511 8564.8855)
    ))
    ; P2225 -- see feature_dimensions_mm.csv
    ("05_STONE_JOINTS" 0 (
      (4213.7405 8229.0076) (4534.3511 8229.0076)
    ))
    ; P2226 -- see feature_dimensions_mm.csv
    ("05_STONE_JOINTS" 0 (
      (4213.7405 8152.6718) (4213.7405 8229.0076)
    ))
    ; P2227 -- see feature_dimensions_mm.csv
    ("05_STONE_JOINTS" 0 (
      (4213.7405 8076.3359) (4213.7405 8152.6718)
    ))
    ; P2228 -- see feature_dimensions_mm.csv
    ("05_STONE_JOINTS" 0 (
      (4290.0763 1969.4656) (4272.2595 1984.7328)
    ))
    ; P2229 -- see feature_dimensions_mm.csv
    ("05_STONE_JOINTS" 0 (
      (4332.5496 8076.3359) (4518.7939 8076.3359)
    ))
    ; P2230 -- see feature_dimensions_mm.csv
    ("05_STONE_JOINTS" 0 (
      (4519.084 1633.5878) (4992.3664 1633.5878)
    ))
    ; P2231 -- see feature_dimensions_mm.csv
    ("05_STONE_JOINTS" 0 (
      (4519.084 1282.4427) (4992.3664 1282.4427)
    ))
    ; P2232 -- see feature_dimensions_mm.csv
    ("05_STONE_JOINTS" 0 (
      (4519.084 931.2977) (4992.3664 931.2977)
    ))
    ; P2233 -- see feature_dimensions_mm.csv
    ("05_STONE_JOINTS" 0 (
      (4885.4962 9572.5191) (4534.3511 9572.5191)
    ))
    ; P2234 -- see feature_dimensions_mm.csv
    ("05_STONE_JOINTS" 0 (
      (4534.3511 9496.1832) (4534.3511 9557.2519) (4534.3511 9572.5191)
    ))
    ; P2235 -- see feature_dimensions_mm.csv
    ("05_STONE_JOINTS" 0 (
      (4534.3511 9496.1832) (4885.4962 9496.1832)
    ))
    ; P2236 -- see feature_dimensions_mm.csv
    ("05_STONE_JOINTS" 0 (
      (4534.3511 9419.8473) (4534.3511 9496.1832)
    ))
    ; P2237 -- see feature_dimensions_mm.csv
    ("05_STONE_JOINTS" 0 (
      (4534.3511 9419.8473) (4885.4962 9419.8473)
    ))
    ; P2238 -- see feature_dimensions_mm.csv
    ("05_STONE_JOINTS" 0 (
      (4534.3511 9328.2443) (4534.3511 9419.8473)
    ))
    ; P2239 -- see feature_dimensions_mm.csv
    ("05_STONE_JOINTS" 0 (
      (4534.3511 9328.2443) (4885.4962 9328.2443)
    ))
    ; P2240 -- see feature_dimensions_mm.csv
    ("05_STONE_JOINTS" 0 (
      (4534.3511 9236.6412) (4534.3511 9328.2443)
    ))
    ; P2241 -- see feature_dimensions_mm.csv
    ("05_STONE_JOINTS" 0 (
      (4534.3511 9236.6412) (4549.6183 9236.6412)
    ))
    ; P2242 -- see feature_dimensions_mm.csv
    ("05_STONE_JOINTS" 0 (
      (4534.3511 8900.7634) (4549.6183 8900.7634)
    ))
    ; P2243 -- see feature_dimensions_mm.csv
    ("05_STONE_JOINTS" 0 (
      (4534.3511 8824.4275) (4534.3511 8900.7634)
    ))
    ; P2244 -- see feature_dimensions_mm.csv
    ("05_STONE_JOINTS" 0 (
      (4534.3511 8824.4275) (4885.4962 8824.4275)
    ))
    ; P2245 -- see feature_dimensions_mm.csv
    ("05_STONE_JOINTS" 0 (
      (4534.3511 8748.0916) (4534.3511 8824.4275)
    ))
    ; P2246 -- see feature_dimensions_mm.csv
    ("05_STONE_JOINTS" 0 (
      (4534.3511 8748.0916) (4885.4962 8748.0916)
    ))
    ; P2247 -- see feature_dimensions_mm.csv
    ("05_STONE_JOINTS" 0 (
      (4534.3511 8656.4885) (4534.3511 8748.0916)
    ))
    ; P2248 -- see feature_dimensions_mm.csv
    ("05_STONE_JOINTS" 0 (
      (4534.3511 8656.4885) (4885.4962 8656.4885)
    ))
    ; P2249 -- see feature_dimensions_mm.csv
    ("05_STONE_JOINTS" 0 (
      (4534.3511 8564.8855) (4534.3511 8656.4885)
    ))
    ; P2250 -- see feature_dimensions_mm.csv
    ("05_STONE_JOINTS" 0 (
      (4534.3511 8564.8855) (4549.6183 8564.8855)
    ))
    ; P2251 -- see feature_dimensions_mm.csv
    ("05_STONE_JOINTS" 0 (
      (4534.3511 8229.0076) (4549.6183 8229.0076)
    ))
    ; P2252 -- see feature_dimensions_mm.csv
    ("05_STONE_JOINTS" 0 (
      (4534.3511 8152.6718) (4534.3511 8229.0076)
    ))
    ; P2253 -- see feature_dimensions_mm.csv
    ("05_STONE_JOINTS" 0 (
      (4534.3511 8152.6718) (4641.2214 8152.6718)
    ))
    ; P2254 -- see feature_dimensions_mm.csv
    ("05_STONE_JOINTS" 0 (
      (4534.3511 8076.3359) (4534.3511 8152.6718)
    ))
    ; P2255 -- see feature_dimensions_mm.csv
    ("05_STONE_JOINTS" 0 (
      (4549.6183 9236.6412) (4870.229 9236.6412)
    ))
    ; P2256 -- see feature_dimensions_mm.csv
    ("05_STONE_JOINTS" 0 (
      (4549.6183 9160.3053) (4549.6183 9236.6412)
    ))
    ; P2257 -- see feature_dimensions_mm.csv
    ("05_STONE_JOINTS" 0 (
      (4549.6183 9083.9695) (4549.6183 9160.3053)
    ))
    ; P2258 -- see feature_dimensions_mm.csv
    ("05_STONE_JOINTS" 0 (
      (4549.6183 8992.3664) (4549.6183 9083.9695)
    ))
    ; P2259 -- see feature_dimensions_mm.csv
    ("05_STONE_JOINTS" 0 (
      (4549.6183 8900.7634) (4549.6183 8992.3664)
    ))
    ; P2260 -- see feature_dimensions_mm.csv
    ("05_STONE_JOINTS" 0 (
      (4549.6183 8900.7634) (4870.229 8900.7634)
    ))
    ; P2261 -- see feature_dimensions_mm.csv
    ("05_STONE_JOINTS" 0 (
      (4549.6183 8564.8855) (4641.2214 8564.8855)
    ))
    ; P2262 -- see feature_dimensions_mm.csv
    ("05_STONE_JOINTS" 0 (
      (4549.6183 8488.5496) (4549.6183 8564.8855)
    ))
    ; P2263 -- see feature_dimensions_mm.csv
    ("05_STONE_JOINTS" 0 (
      (4549.6183 8412.2137) (4549.6183 8488.5496)
    ))
    ; P2264 -- see feature_dimensions_mm.csv
    ("05_STONE_JOINTS" 0 (
      (4549.6183 8320.6107) (4549.6183 8412.2137)
    ))
    ; P2265 -- see feature_dimensions_mm.csv
    ("05_STONE_JOINTS" 0 (
      (4549.6183 8229.0076) (4549.6183 8320.6107)
    ))
    ; P2266 -- see feature_dimensions_mm.csv
    ("05_STONE_JOINTS" 0 (
      (4549.6183 8229.0076) (4641.2214 8229.0076)
    ))
    ; P2267 -- see feature_dimensions_mm.csv
    ("05_STONE_JOINTS" 0 (
      (4595.4198 5969.4656) (4992.3664 5969.4656) (8671.7557 5969.4656)
    ))
    ; P2268 -- see feature_dimensions_mm.csv
    ("05_STONE_JOINTS" 0 (
      (4641.2214 8229.0076) (4641.2214 8320.6107)
    ))
    ; P2269 -- see feature_dimensions_mm.csv
    ("05_STONE_JOINTS" 0 (
      (4641.2214 8152.6718) (4641.2214 8229.0076)
    ))
    ; P2270 -- see feature_dimensions_mm.csv
    ("05_STONE_JOINTS" 0 (
      (4885.4962 8122.1374) (4641.2214 8122.1374) (4641.2214 8152.6718)
    ))
    ; P2271 -- see feature_dimensions_mm.csv
    ("05_STONE_JOINTS" 0 (
      (4669.2061 1984.7328) (4656.4885 1969.4656)
    ))
    ; P2272 -- see feature_dimensions_mm.csv
    ("05_STONE_JOINTS" 0 (
      (4669.2061 1984.7328) (4992.3664 1984.7328) (4992.3664 2213.7405)
    ))
    ; P2273 -- see feature_dimensions_mm.csv
    ("05_STONE_JOINTS" 0 (
      (4732.8244 2061.0687) (4669.2061 1984.7328)
    ))
    ; P2274 -- see feature_dimensions_mm.csv
    ("05_STONE_JOINTS" 0 (
      (4746.4275 8076.3359) (4885.4962 8076.3359)
    ))
    ; P2275 -- see feature_dimensions_mm.csv
    ("05_STONE_JOINTS" 0 (
      (4860.0916 8641.2214) (4885.4962 8641.2214)
    ))
    ; P2276 -- see feature_dimensions_mm.csv
    ("05_STONE_JOINTS" 0 (
      (4870.229 9236.6412) (4885.4962 9236.6412)
    ))
    ; P2277 -- see feature_dimensions_mm.csv
    ("05_STONE_JOINTS" 0 (
      (4870.229 9160.3053) (4870.229 9236.6412)
    ))
    ; P2278 -- see feature_dimensions_mm.csv
    ("05_STONE_JOINTS" 0 (
      (4870.229 9160.3053) (4992.3664 9160.3053)
    ))
    ; P2279 -- see feature_dimensions_mm.csv
    ("05_STONE_JOINTS" 0 (
      (4870.229 9083.9695) (4870.229 9160.3053)
    ))
    ; P2280 -- see feature_dimensions_mm.csv
    ("05_STONE_JOINTS" 0 (
      (4870.229 9083.9695) (4992.3664 9083.9695)
    ))
    ; P2281 -- see feature_dimensions_mm.csv
    ("05_STONE_JOINTS" 0 (
      (4870.229 8992.3664) (4870.229 9083.9695)
    ))
    ; P2282 -- see feature_dimensions_mm.csv
    ("05_STONE_JOINTS" 0 (
      (4870.229 8992.3664) (4992.3664 8992.3664)
    ))
    ; P2283 -- see feature_dimensions_mm.csv
    ("05_STONE_JOINTS" 0 (
      (4870.229 8900.7634) (4870.229 8992.3664)
    ))
    ; P2284 -- see feature_dimensions_mm.csv
    ("05_STONE_JOINTS" 0 (
      (4870.229 8900.7634) (4885.4962 8900.7634)
    ))
    ; P2285 -- see feature_dimensions_mm.csv
    ("05_STONE_JOINTS" 0 (
      (4992.3664 9236.6412) (4992.3664 9557.2519) (4992.3664 9572.5191) (4885.4962 9572.5191)
    ))
    ; P2286 -- see feature_dimensions_mm.csv
    ("05_STONE_JOINTS" 0 (
      (4885.4962 9496.1832) (4885.4962 9557.2519) (4885.4962 9572.5191)
    ))
    ; P2287 -- see feature_dimensions_mm.csv
    ("05_STONE_JOINTS" 0 (
      (4885.4962 9419.8473) (4885.4962 9496.1832)
    ))
    ; P2288 -- see feature_dimensions_mm.csv
    ("05_STONE_JOINTS" 0 (
      (4885.4962 9328.2443) (4885.4962 9419.8473)
    ))
    ; P2289 -- see feature_dimensions_mm.csv
    ("05_STONE_JOINTS" 0 (
      (4885.4962 9236.6412) (4885.4962 9328.2443)
    ))
    ; P2290 -- see feature_dimensions_mm.csv
    ("05_STONE_JOINTS" 0 (
      (4885.4962 9236.6412) (4992.3664 9236.6412)
    ))
    ; P2291 -- see feature_dimensions_mm.csv
    ("05_STONE_JOINTS" 0 (
      (4885.4962 8900.7634) (4992.3664 8900.7634)
    ))
    ; P2292 -- see feature_dimensions_mm.csv
    ("05_STONE_JOINTS" 0 (
      (4885.4962 8824.4275) (4885.4962 8900.7634)
    ))
    ; P2293 -- see feature_dimensions_mm.csv
    ("05_STONE_JOINTS" 0 (
      (4885.4962 8748.0916) (4885.4962 8824.4275)
    ))
    ; P2294 -- see feature_dimensions_mm.csv
    ("05_STONE_JOINTS" 0 (
      (4885.4962 8656.4885) (4885.4962 8748.0916)
    ))
    ; P2295 -- see feature_dimensions_mm.csv
    ("05_STONE_JOINTS" 0 (
      (4885.4962 8641.2214) (4885.4962 8656.4885)
    ))
    ; P2296 -- see feature_dimensions_mm.csv
    ("05_STONE_JOINTS" 0 (
      (4885.4962 8641.2214) (4992.3664 8641.2214) (4992.3664 8900.7634)
    ))
    ; P2297 -- see feature_dimensions_mm.csv
    ("05_STONE_JOINTS" 0 (
      (4992.3664 8122.1374) (4977.0992 8122.1374) (4885.4962 8122.1374)
    ))
    ; P2298 -- see feature_dimensions_mm.csv
    ("05_STONE_JOINTS" 0 (
      (4885.4962 8076.3359) (4885.4962 8122.1374)
    ))
    ; P2299 -- see feature_dimensions_mm.csv
    ("05_STONE_JOINTS" 0 (
      (4885.4962 8076.3359) (4932.6718 8076.3359) (4977.0992 8076.3359) (4992.3664 8076.3359) (4992.3664 8122.1374)
    ))
    ; P2300 -- see feature_dimensions_mm.csv
    ("05_STONE_JOINTS" 0 (
      (4992.3664 9160.3053) (4992.3664 9236.6412)
    ))
    ; P2301 -- see feature_dimensions_mm.csv
    ("05_STONE_JOINTS" 0 (
      (4992.3664 9083.9695) (4992.3664 9160.3053)
    ))
    ; P2302 -- see feature_dimensions_mm.csv
    ("05_STONE_JOINTS" 0 (
      (4992.3664 8992.3664) (4992.3664 9083.9695)
    ))
    ; P2303 -- see feature_dimensions_mm.csv
    ("05_STONE_JOINTS" 0 (
      (4992.3664 8900.7634) (4992.3664 8992.3664)
    ))
    ; P2304 -- see feature_dimensions_mm.csv
    ("05_STONE_JOINTS" 0 (
      (7022.9008 8122.1374) (4992.3664 8122.1374)
    ))
    ; P2305 -- see feature_dimensions_mm.csv
    ("05_STONE_JOINTS" 0 (
      (4992.3664 7358.7786) (8671.7557 7358.7786)
    ))
    ; P2306 -- see feature_dimensions_mm.csv
    ("05_STONE_JOINTS" 0 (
      (4992.3664 7358.7786) (4992.3664 7312.9771)
    ))
    ; P2307 -- see feature_dimensions_mm.csv
    ("05_STONE_JOINTS" 0 (
      (4992.3664 5343.5115) (5221.374 5343.5115)
    ))
    ; P2308 -- see feature_dimensions_mm.csv
    ("05_STONE_JOINTS" 0 (
      (4992.3664 4717.5573) (5221.374 4717.5573)
    ))
    ; P2309 -- see feature_dimensions_mm.csv
    ("05_STONE_JOINTS" 0 (
      (4992.3664 4091.6031) (5221.374 4091.6031)
    ))
    ; P2310 -- see feature_dimensions_mm.csv
    ("05_STONE_JOINTS" 0 (
      (4992.3664 2641.2214) (4992.3664 2305.3435)
    ))
    ; P2311 -- see feature_dimensions_mm.csv
    ("05_STONE_JOINTS" 0 (
      (4992.3664 2641.2214) (4992.3664 2839.6947) (5221.374 2839.6947) (5221.374 3465.6489) (5175.5725 3465.6489)
      (5175.5725 3267.1756)
    ))
    ; P2312 -- see feature_dimensions_mm.csv
    ("05_STONE_JOINTS" 0 (
      (4992.3664 2305.3435) (4992.3664 2213.7405)
    ))
    ; P2313 -- see feature_dimensions_mm.csv
    ("05_STONE_JOINTS" 0 (
      (4992.3664 2213.7405) (5221.374 2213.7405)
    ))
    ; P2314 -- see feature_dimensions_mm.csv
    ("05_STONE_JOINTS" 0 (
      (4992.3664 1587.7863) (5221.374 1587.7863)
    ))
    ; P2315 -- see feature_dimensions_mm.csv
    ("05_STONE_JOINTS" 0 (
      (4992.3664 961.8321) (5297.7099 961.8321) (6045.8015 961.8321) (6335.8779 961.8321) (7404.5802 961.8321)
      (7694.6565 961.8321)
    ))
    ; P2316 -- see feature_dimensions_mm.csv
    ("05_STONE_JOINTS" 0 (
      (4992.3664 793.8931) (8473.2824 793.8931)
    ))
    ; P2317 -- see feature_dimensions_mm.csv
    ("05_STONE_JOINTS" 0 (
      (5160.3053 7740.458) (8671.7557 7740.458) (8671.7557 7755.7252)
    ))
    ; P2318 -- see feature_dimensions_mm.csv
    ("05_STONE_JOINTS" 0 (
      (5160.3053 6961.8321) (5190.8397 6961.8321) (5251.9084 6961.8321) (5268.2595 6961.8321) (5282.4427 6961.8321)
      (5343.5115 6961.8321) (5374.0458 6961.8321) (5435.1145 6961.8321) (5465.6489 6961.8321) (5544.1679 6961.8321)
      (5820.0611 6961.8321) (6095.9695 6961.8321) (6371.8626 6961.8321) (6647.771 6961.8321) (6923.6641 6961.8321)
      (7199.5573 6961.8321) (7475.4656 6961.8321) (7751.3588 6961.8321) (8027.2672 6961.8321)
    ))
    ; P2319 -- see feature_dimensions_mm.csv
    ("05_STONE_JOINTS" 0 (
      (6122.1374 5343.5115) (6259.542 5343.5115)
    ))
    ; P2320 -- see feature_dimensions_mm.csv
    ("05_STONE_JOINTS" 0 (
      (6122.1374 4717.5573) (6259.542 4717.5573)
    ))
    ; P2321 -- see feature_dimensions_mm.csv
    ("05_STONE_JOINTS" 0 (
      (6122.1374 4091.6031) (6259.542 4091.6031)
    ))
    ; P2322 -- see feature_dimensions_mm.csv
    ("05_STONE_JOINTS" 0 (
      (6122.1374 2213.7405) (6259.542 2213.7405)
    ))
    ; P2323 -- see feature_dimensions_mm.csv
    ("05_STONE_JOINTS" 0 (
      (6122.1374 1587.7863) (6259.542 1587.7863)
    ))
    ; P2324 -- see feature_dimensions_mm.csv
    ("05_STONE_JOINTS" 0 (
      (8671.7557 8122.1374) (7039.6947 8122.1374)
    ))
    ; P2325 -- see feature_dimensions_mm.csv
    ("05_STONE_JOINTS" 0 (
      (7480.916 5343.5115) (7618.3206 5343.5115)
    ))
    ; P2326 -- see feature_dimensions_mm.csv
    ("05_STONE_JOINTS" 0 (
      (7480.916 4091.6031) (7618.3206 4091.6031)
    ))
    ; P2327 -- see feature_dimensions_mm.csv
    ("05_STONE_JOINTS" 0 (
      (7480.916 4091.6031) (7480.916 3465.6489)
    ))
    ; P2328 -- see feature_dimensions_mm.csv
    ("05_STONE_JOINTS" 0 (
      (7480.916 4091.6031) (7480.916 4717.5573) (7618.3206 4717.5573)
    ))
    ; P2329 -- see feature_dimensions_mm.csv
    ("05_STONE_JOINTS" 0 (
      (7480.916 3465.6489) (7618.3206 3465.6489)
    ))
    ; P2330 -- see feature_dimensions_mm.csv
    ("05_STONE_JOINTS" 0 (
      (7480.916 3465.6489) (7480.916 2839.6947)
    ))
    ; P2331 -- see feature_dimensions_mm.csv
    ("05_STONE_JOINTS" 1 (
      (7480.916 2839.6947) (7480.916 2213.7405) (7618.3206 2213.7405) (7618.3206 2839.6947)
    ))
    ; P2332 -- see feature_dimensions_mm.csv
    ("05_STONE_JOINTS" 0 (
      (7480.916 1587.7863) (7618.3206 1587.7863)
    ))
    ; P2333 -- see feature_dimensions_mm.csv
    ("05_STONE_JOINTS" 0 (
      (8442.7481 961.8321) (8473.2824 961.8321)
    ))
    ; P2334 -- see feature_dimensions_mm.csv
    ("05_STONE_JOINTS" 0 (
      (8519.084 5343.5115) (8671.7557 5343.5115)
    ))
    ; P2335 -- see feature_dimensions_mm.csv
    ("05_STONE_JOINTS" 0 (
      (8519.084 4717.5573) (8671.7557 4717.5573)
    ))
    ; P2336 -- see feature_dimensions_mm.csv
    ("05_STONE_JOINTS" 0 (
      (8519.084 4091.6031) (8671.7557 4091.6031)
    ))
    ; P2337 -- see feature_dimensions_mm.csv
    ("05_STONE_JOINTS" 0 (
      (10290.0763 5969.4656) (10687.0229 5969.4656)
    ))
    ; P2338 -- see feature_dimensions_mm.csv
    ("05_STONE_JOINTS" 0 (
      (10290.0763 290.0763) (10290.0763 213.7405) (10290.0763 122.1374) (10290.0763 15.2672)
    ))
    ; P2339 -- see feature_dimensions_mm.csv
    ("05_STONE_JOINTS" 0 (
      (13832.0611 3267.1756) (10519.084 3267.1756)
    ))
    ; P2340 -- see feature_dimensions_mm.csv
    ("05_STONE_JOINTS" 0 (
      (10519.084 2961.8321) (11038.1679 2961.8321) (11038.1679 3099.2366) (11160.3053 3099.2366) (11160.3053 2961.8321)
      (11312.9771 2961.8321) (11312.9771 3099.2366) (11435.1145 3099.2366) (11435.1145 2961.8321) (11603.0534 2961.8321)
      (11603.0534 3099.2366) (11725.1908 3099.2366)
    ))
    ; P2341 -- see feature_dimensions_mm.csv
    ("05_STONE_JOINTS" 0 (
      (10519.084 2641.2214) (13832.0611 2641.2214)
    ))
    ; P2342 -- see feature_dimensions_mm.csv
    ("05_STONE_JOINTS" 0 (
      (10519.084 2305.3435) (10962.6718 2305.3435)
    ))
    ; P2343 -- see feature_dimensions_mm.csv
    ("05_STONE_JOINTS" 0 (
      (10519.084 2008.7176) (10547.0687 1984.7328)
    ))
    ; P2344 -- see feature_dimensions_mm.csv
    ("05_STONE_JOINTS" 0 (
      (10519.084 1633.5878) (10580.1527 1633.5878)
    ))
    ; P2345 -- see feature_dimensions_mm.csv
    ("05_STONE_JOINTS" 0 (
      (10519.084 1282.4427) (10519.084 1633.5878)
    ))
    ; P2346 -- see feature_dimensions_mm.csv
    ("05_STONE_JOINTS" 0 (
      (10519.084 1633.5878) (10519.084 1984.7328) (10547.0687 1984.7328)
    ))
    ; P2347 -- see feature_dimensions_mm.csv
    ("05_STONE_JOINTS" 0 (
      (10519.084 1282.4427) (10580.1527 1282.4427) (10580.1527 1633.5878)
    ))
    ; P2348 -- see feature_dimensions_mm.csv
    ("05_STONE_JOINTS" 0 (
      (10519.084 931.2977) (10519.084 1282.4427)
    ))
    ; P2349 -- see feature_dimensions_mm.csv
    ("05_STONE_JOINTS" 0 (
      (10519.084 931.2977) (10580.1527 931.2977)
    ))
    ; P2350 -- see feature_dimensions_mm.csv
    ("05_STONE_JOINTS" 0 (
      (10519.084 931.2977) (10519.084 656.4885) (10580.1527 656.4885) (10748.0916 656.4885) (10854.9618 656.4885)
      (10870.229 656.4885) (11847.3282 656.4885) (11908.3969 656.4885) (11923.6641 656.4885)
    ))
    ; P2351 -- see feature_dimensions_mm.csv
    ("05_STONE_JOINTS" 0 (
      (10547.0687 1984.7328) (10564.8855 1969.4656)
    ))
    ; P2352 -- see feature_dimensions_mm.csv
    ("05_STONE_JOINTS" 0 (
      (10610.687 1862.5954) (10580.1527 1862.5954) (10580.1527 1633.5878)
    ))
    ; P2353 -- see feature_dimensions_mm.csv
    ("05_STONE_JOINTS" 0 (
      (10962.6718 2305.3435) (10956.1221 2300.2901)
    ))
    ; P2354 -- see feature_dimensions_mm.csv
    ("05_STONE_JOINTS" 0 (
      (10987.0229 2324.1221) (10962.6718 2305.3435)
    ))
    ; P2355 -- see feature_dimensions_mm.csv
    ("05_STONE_JOINTS" 0 (
      (11725.1908 2961.8321) (12412.2137 2961.8321) (12412.2137 3099.2366) (12534.3511 3099.2366) (12534.3511 2961.8321)
      (12702.2901 2961.8321)
    ))
    ; P2356 -- see feature_dimensions_mm.csv
    ("05_STONE_JOINTS" 0 (
      (11754.8855 2305.3435) (11730.5344 2324.1221)
    ))
    ; P2357 -- see feature_dimensions_mm.csv
    ("05_STONE_JOINTS" 0 (
      (11754.8855 2305.3435) (12306.1832 2305.3435)
    ))
    ; P2358 -- see feature_dimensions_mm.csv
    ("05_STONE_JOINTS" 0 (
      (11761.4351 2300.2901) (11754.8855 2305.3435)
    ))
    ; P2359 -- see feature_dimensions_mm.csv
    ("05_STONE_JOINTS" 0 (
      (12154.5802 2122.5954) (12138.0916 2088.3817) (12127.1603 2061.0687) (11933.9084 2061.0687)
    ))
    ; P2360 -- see feature_dimensions_mm.csv
    ("05_STONE_JOINTS" 0 (
      (12306.1832 2305.3435) (12299.6336 2300.2901) (12270.4733 2274.6107) (12243.145 2247.1908) (12217.8015 2218.1527)
      (12194.5191 2187.6183) (12173.4198 2155.7252)
    ))
    ; P2361 -- see feature_dimensions_mm.csv
    ("05_STONE_JOINTS" 0 (
      (12330.5344 2324.1221) (12306.1832 2305.3435)
    ))
    ; P2362 -- see feature_dimensions_mm.csv
    ("05_STONE_JOINTS" 0 (
      (12396.9466 2365.8473) (12363.0076 2346.0)
    ))
    ; P2363 -- see feature_dimensions_mm.csv
    ("05_STONE_JOINTS" 0 (
      (12544.229 2423.1908) (12505.9847 2412.2901) (12468.5954 2399.0534) (12432.1832 2383.542)
    ))
    ; P2364 -- see feature_dimensions_mm.csv
    ("05_STONE_JOINTS" 0 (
      (12557.2519 2610.687) (12847.3282 2610.687)
    ))
    ; P2365 -- see feature_dimensions_mm.csv
    ("05_STONE_JOINTS" 0 (
      (12824.4275 2961.8321) (12992.3664 2961.8321)
    ))
    ; P2366 -- see feature_dimensions_mm.csv
    ("05_STONE_JOINTS" 0 (
      (13098.3969 2305.3435) (13074.0458 2324.1221)
    ))
    ; P2367 -- see feature_dimensions_mm.csv
    ("05_STONE_JOINTS" 0 (
      (13098.3969 2305.3435) (13832.0611 2305.3435) (13832.0611 2641.2214)
    ))
    ; P2368 -- see feature_dimensions_mm.csv
    ("05_STONE_JOINTS" 0 (
      (13104.9466 2300.2901) (13098.3969 2305.3435)
    ))
    ; P2369 -- see feature_dimensions_mm.csv
    ("05_STONE_JOINTS" 0 (
      (13114.5038 2961.8321) (13832.0611 2961.8321) (13832.0611 2641.2214)
    ))
    ; P2370 -- see feature_dimensions_mm.csv
    ("05_STONE_JOINTS" 0 (
      (13832.0611 5969.4656) (13435.1145 5969.4656) (13435.1145 6015.2672) (13230.3664 6015.2672) (13190.8397 6015.2672)
      (13190.8397 6155.6183) (13190.8397 6244.2748)
    ))
    ; P2371 -- see feature_dimensions_mm.csv
    ("05_STONE_JOINTS" 0 (
      (13250.0 2122.5954) (13231.1603 2155.7252)
    ))
    ; P2372 -- see feature_dimensions_mm.csv
    ("05_STONE_JOINTS" 0 (
      (13282.4427 656.4885) (13312.9771 656.4885) (13557.2519 656.4885)
    ))
    ; P2373 -- see feature_dimensions_mm.csv
    ("05_STONE_JOINTS" 0 (
      (13325.6947 1984.7328) (13293.3588 2012.4427)
    ))
    ; P2374 -- see feature_dimensions_mm.csv
    ("05_STONE_JOINTS" 0 (
      (13300.2443 1984.7328) (13325.6947 1984.7328)
    ))
    ; P2375 -- see feature_dimensions_mm.csv
    ("05_STONE_JOINTS" 0 (
      (13343.5115 1969.4656) (13325.6947 1984.7328)
    ))
    ; P2376 -- see feature_dimensions_mm.csv
    ("05_STONE_JOINTS" 0 (
      (13557.2519 1633.5878) (13557.2519 1862.5954)
    ))
    ; P2377 -- see feature_dimensions_mm.csv
    ("05_STONE_JOINTS" 0 (
      (13557.2519 1633.5878) (13832.0611 1633.5878)
    ))
    ; P2378 -- see feature_dimensions_mm.csv
    ("05_STONE_JOINTS" 0 (
      (13557.2519 1633.5878) (13557.2519 1282.4427) (13832.0611 1282.4427) (13832.0611 1633.5878)
    ))
    ; P2379 -- see feature_dimensions_mm.csv
    ("05_STONE_JOINTS" 1 (
      (13557.2519 656.4885) (13832.0611 656.4885) (13832.0611 931.2977) (13557.2519 931.2977)
    ))
    ; P2380 -- see feature_dimensions_mm.csv
    ("05_STONE_JOINTS" 0 (
      (13737.9084 1984.7328) (13725.1908 1969.4656)
    ))
    ; P2381 -- see feature_dimensions_mm.csv
    ("05_STONE_JOINTS" 0 (
      (13737.9084 1984.7328) (13832.0611 1984.7328) (13832.0611 1633.5878)
    ))
    ; P2382 -- see feature_dimensions_mm.csv
    ("05_STONE_JOINTS" 0 (
      (13801.5267 2061.0687) (13737.9084 1984.7328)
    ))
    ; P2383 -- see feature_dimensions_mm.csv
    ("05_STONE_JOINTS" 0 (
      (13832.0611 6992.3664) (13832.0611 7526.7176)
    ))
    ; P2384 -- see feature_dimensions_mm.csv
    ("05_STONE_JOINTS" 1 (
      (13832.0611 7526.7176) (13832.0611 7541.9847) (10290.0763 7541.9847) (10290.0763 7526.7176)
    ))
    ; P2385 -- see feature_dimensions_mm.csv
    ("05_STONE_JOINTS" 1 (
      (13832.0611 6992.3664) (13832.0611 6977.0992) (13832.0611 6656.4885) (13832.0611 6564.8855) (10290.0763 6564.8855)
      (10290.0763 6656.4885) (10290.0763 6977.0992) (10290.0763 6992.3664)
    ))
    ; P2386 -- see feature_dimensions_mm.csv
    ("05_STONE_JOINTS" 1 (
      (6122.1374 3465.6489) (6122.1374 2839.6947) (6259.542 2839.6947) (6259.542 3465.6489)
    ))
    ; P2387 -- see feature_dimensions_mm.csv
    ("06_ORNAMENT" 0 (
      (1358.7786 5465.6489) (1358.7786 5007.6336)
    ))
    ; P2388 -- see feature_dimensions_mm.csv
    ("06_ORNAMENT" 1 (
      (1358.7786 5007.6336) (1387.1756 4987.771) (1419.3435 4967.4809) (1454.7786 4947.084) (1492.9618 4926.9008)
      (1533.3588 4907.2672) (1575.4351 4888.4733) (1618.6718 4870.8702) (1662.5496 4854.7634) (1677.7099 4849.8473)
      (1671.2061 4850.3969) (1628.5496 4852.2595) (1586.2901 4852.4733) (1545.0229 4851.1298) (1505.3435 4848.3206)
      (1467.8168 4844.1527) (1433.0382 4838.7176) (1401.5878 4832.1069) (1374.0458 4824.4275) (1403.8168 4814.0153)
      (1436.9618 4804.3359) (1472.9618 4795.5267) (1511.2672 4787.7405) (1551.3435 4781.145) (1592.6565 4775.8626)
      (1634.6718 4772.0611) (1676.8397 4769.8931) (1713.5725 4769.5267) (1706.2748 4767.7405) (1666.2137 4755.9847)
      (1626.626 4742.5191) (1588.0153 4727.6641) (1550.8702 4711.7252) (1515.6794 4694.9771) (1482.9618 4677.7252)
      (1453.2061 4660.2748) (1426.916 4642.916) (1404.5802 4625.9542) (1435.4962 4626.8397) (1469.2366 4629.6183)
      (1505.2519 4634.229) (1543.0076 4640.626) (1581.9542 4648.7328) (1621.542 4658.5344) (1661.2214 4669.9389)
      (1700.4733 4682.9313) (1738.7328 4697.4351) (1739.6031 4697.8015) (1727.0229 4688.3053) (1695.5573 4662.1527)
      (1665.2061 4634.626) (1636.2901 4606.2137) (1609.1298 4577.3588) (1584.0763 4548.5344) (1561.4504 4520.1985)
      (1541.5878 4492.8092) (1524.8092 4466.8397) (1511.4504 4442.7481) (1539.0229 4455.4504) (1568.3969 4470.9618)
      (1599.084 4489.0382) (1630.626 4509.3893) (1662.5344 4531.7863) (1694.3664 4555.9542) (1725.6489 4581.6489)
      (1755.8779 4608.5954) (1774.2595 4626.4885) (1762.8397 4603.4504) (1747.8473 4569.2672) (1734.5344 4534.8397)
      (1722.9618 4500.626) (1718.0611 4483.7863) (1713.2061 4488.8397) (1703.8168 4496.1832) (1693.771 4501.1756)
      (1682.7481 4503.9847) (1671.0076 4504.8855) (1658.8702 4504.1527) (1646.626 4502.0763) (1634.5802 4498.9008)
      (1623.0076 4494.916) (1612.2137 4490.3817) (1601.5573 4484.7939) (1590.458 4477.6641) (1579.3588 4469.3282)
      (1568.7023 4460.1069) (1558.9008 4450.3053) (1550.3817 4440.2748) (1543.5878 4430.3206) (1538.9313 4420.7634)
      (1536.5344 4411.0382) (1536.0458 4400.5649) (1537.1756 4389.7405) (1539.6489 4378.8855) (1540.4122 4376.626)
      (1532.2137 4381.6794) (1522.8397 4385.3588) (1512.5496 4387.4198) (1501.5878 4388.0916) (1490.2748 4387.5573)
      (1478.8397 4386.0153) (1467.5878 4383.6794) (1464.7481 4382.916) (1450.3817 4396.9466) (1458.6565 4381.2519)
      (1456.7939 4380.7481) (1446.7176 4377.4046) (1436.7634 4373.2824) (1426.4122 4368.0305) (1416.0611 4361.8931)
      (1406.1069 4355.0992) (1396.9618 4347.8779) (1389.0076 4340.4885) (1382.6565 4333.145) (1378.3206 4326.1069)
      (1376.0916 4318.9313) (1375.6336 4311.2214) (1376.687 4303.2519) (1378.9924 4295.2519) (1382.2748 4287.4962)
      (1386.2901 4280.2748) (1390.7481 4273.8168) (1395.4198 4268.3969) (1400.8702 4263.7557) (1407.5878 4259.5267)
      (1415.2214 4255.8321) (1423.3435 4252.7634) (1431.5878 4250.458) (1439.5573 4249.0076) (1446.8702 4248.5344)
      (1453.1298 4249.1603) (1458.7939 4251.2824) (1464.3969 4254.9771) (1469.7557 4259.8321) (1474.6412 4265.4504)
      (1478.8397 4271.4504) (1482.1374 4277.4198) (1484.3206 4282.9466) (1485.1908 4287.6336) (1483.8779 4291.7863)
      (1480.2137 4295.9389) (1475.0382 4299.9695) (1469.1603 4303.8015) (1463.4198 4307.3435) (1458.6412 4310.5344)
      (1455.6489 4313.2519) (1455.2672 4315.4198) (1457.7557 4317.2519) (1462.4427 4318.916) (1468.7481 4320.2595)
      (1476.1069 4321.1603) (1483.9237 4321.4809) (1491.6336 4321.084) (1492.626 4320.9008) (1503.4504 4302.6412)
      (1525.3893 4267.3435) (1534.3359 4253.5267) (1533.7405 4248.0916) (1532.3359 4241.313) (1514.8855 4258.1679)
      (1496.1832 4274.8092) (1508.9008 4250.1069) (1523.8321 4223.2824) (1524.4427 4222.2595) (1521.1298 4217.2366)
      (1515.1145 4210.687) (1505.7405 4204.5344) (1492.1985 4198.458) (1476.3664 4192.626) (1460.0763 4187.1756)
      (1445.1908 4182.2595) (1433.5573 4178.0305) (1427.0382 4174.626) (1427.4809 4172.2137) (1436.7481 4170.2443)
      (1453.8779 4168.3359) (1476.4733 4166.9008) (1502.1527 4166.3359) (1528.5191 4167.0382) (1532.4733 4167.4198)
      (1524.3053 4163.4198) (1512.2137 4156.626) (1501.0992 4149.4046) (1491.4504 4142.0153) (1483.7405 4134.6718)
      (1478.4733 4127.6336) (1475.771 4120.458) (1475.2061 4112.7481) (1476.4885 4104.7786) (1479.2824 4096.7786)
      (1483.2824 4089.0229) (1488.1527 4081.8015) (1493.5725 4075.3435) (1499.2366 4069.9237) (1505.8473 4065.2824)
      (1514.0153 4061.0534) (1523.2672 4057.3588) (1533.145 4054.2901) (1543.145 4051.9847) (1552.8244 4050.5344)
      (1561.7099 4050.0611) (1569.313 4050.687) (1576.1832 4052.8092) (1582.9924 4056.5038) (1589.4962 4061.3588)
      (1592.3969 4064.1069) (1593.3893 4062.5496) (1610.0305 4037.7099) (1627.8015 4012.6718) (1632.855 4005.9389)
      (1626.4427 4003.5725) (1616.5344 4011.3588) (1601.6031 4021.9542) (1587.7863 4030.5344) (1595.4656 4014.3053)
      (1604.7634 3996.9466) (1605.0687 3996.4427) (1597.5267 3994.1527) (1577.7557 3988.7023) (1559.6641 3983.7863)
      (1545.542 3979.5573) (1537.6336 3976.1527) (1538.1679 3973.7405) (1549.4198 3971.771) (1570.229 3969.8626)
      (1597.6641 3968.4275) (1622.4275 3967.9847) (1627.6031 3959.9237) (1640.8092 3940.8397) (1655.0382 3921.7252)
      (1670.0916 3902.8702) (1685.8473 3884.5496) (1702.1374 3867.0382) (1704.7634 3864.4733) (1706.8855 3855.4198)
      (1709.9389 3846.5649) (1713.6489 3838.3053) (1717.8015 3830.916) (1722.1374 3824.7328) (1727.1908 3819.4351)
      (1733.4351 3814.5954) (1740.5191 3810.3664) (1748.0611 3806.8702) (1755.7099 3804.229) (1763.1145 3802.5802)
      (1769.9084 3802.0458) (1775.7252 3802.7481) (1780.2748 3804.8397) (1786.2595 3801.5267) (1783.8473 3807.4962)
      (1786.1985 3809.3893) (1791.1603 3814.9466) (1795.6947 3821.374) (1799.5878 3828.229) (1802.6565 3835.0382)
      (1804.687 3841.3588) (1805.4962 3846.7176) (1804.2748 3851.4656) (1800.8702 3856.1985) (1796.0611 3860.8092)
      (1790.6107 3865.1908) (1785.2824 3869.2519) (1780.8397 3872.8855) (1778.0611 3875.9847) (1777.7099 3878.4733)
      (1780.0305 3880.5649) (1784.3817 3882.458) (1790.229 3884.0) (1797.0687 3885.0382) (1804.3206 3885.4046)
      (1811.4809 3884.9466) (1818.0 3883.4962) (1823.3588 3880.916) (1828.0 3876.9924) (1832.626 3871.771)
      (1837.0992 3865.5267) (1841.2214 3858.4733) (1844.855 3850.8702) (1847.8321 3842.9618) (1849.9847 3834.9771)
      (1851.145 3827.1756) (1851.5267 3819.1603) (1851.374 3810.5344) (1850.5802 3801.5267) (1849.0382 3792.3664)
      (1846.6412 3783.2824) (1843.2824 3774.5038) (1838.8702 3766.2595) (1833.2824 3758.7786) (1824.5802 3751.7405)
      (1812.0153 3744.8092) (1797.2977 3738.1374) (1782.1832 3731.9084) (1768.3511 3726.2901) (1757.5573 3721.4504)
      (1751.4962 3717.5725) (1751.9084 3714.8092) (1760.5191 3712.5496) (1776.4275 3710.3817) (1797.4046 3708.7328)
      (1821.2519 3708.0916) (1845.7252 3708.8855) (1868.626 3711.6031) (1887.7099 3716.6718) (1900.7634 3724.5802)
      (1908.2443 3736.3511) (1912.4427 3751.9847) (1913.9389 3770.4122) (1913.2977 3790.5344) (1911.084 3811.2672)
      (1907.8779 3831.5267) (1904.2443 3850.2137) (1900.7634 3866.2595) (1896.9771 3880.458) (1892.1374 3894.1985)
      (1886.4122 3907.2519) (1879.9237 3919.3893) (1872.8092 3930.3817) (1865.2214 3940.0) (1857.2977 3948.0153)
      (1849.1603 3954.1985) (1840.458 3958.3969) (1830.9008 3960.7634) (1826.1679 3961.1145) (1848.4122 3963.8321)
      (1870.4275 3969.8473) (1885.4962 3979.2366) (1894.1221 3993.2061) (1898.9618 4011.7863) (1900.687 4033.6641)
      (1899.9542 4057.5573) (1897.4046 4082.1832) (1893.7099 4106.229) (1889.5267 4128.4275) (1885.4962 4147.4809)
      (1881.1145 4164.3359) (1875.542 4180.6565) (1868.9313 4196.1527) (1861.4504 4210.5649) (1853.2519 4223.6183)
      (1844.4885 4235.0534) (1835.3435 4244.5649) (1825.9542 4251.9084) (1815.9084 4256.9008) (1804.8855 4259.7099)
      (1793.145 4260.6107) (1781.0076 4259.8779) (1777.084 4259.2214) (1778.5496 4277.9389) (1777.8168 4301.8321)
      (1775.2672 4326.458) (1771.5725 4350.5038) (1767.3893 4372.7023) (1763.3588 4391.7557) (1758.9771 4408.6107)
      (1753.8473 4423.6794) (1771.3893 4449.771) (1789.9847 4480.0763) (1807.7252 4511.8931) (1824.3206 4544.8092)
      (1839.4504 4578.458) (1852.8092 4612.4427) (1864.0916 4646.3969) (1873.0076 4679.9084) (1879.2519 4712.6107)
      (1882.4885 4744.1221) (1882.458 4768.3359) (1889.313 4782.4427) (1883.6947 4780.2595) (1896.1832 4790.8397)
      (1879.6489 4791.374) (1903.0534 4799.2366) (1882.3817 4807.8931) (1909.9237 4807.6336) (1888.7634 4824.2595)
      (1916.7939 4816.0305) (1899.4656 4837.4962) (1923.6641 4824.4275) (1901.4198 4863.9084) (1874.7328 4904.4885)
      (1844.2443 4945.6947) (1810.5649 4987.084) (1774.3206 5028.2137) (1736.1221 5068.6412) (1726.3511 5078.3511)
      (1748.2901 5084.3511) (1763.3588 5093.7405) (1771.9847 5107.7099) (1776.8244 5126.2901) (1778.5496 5148.1679)
      (1777.8168 5172.0611) (1775.2672 5196.687) (1771.5725 5220.7328) (1767.3893 5242.9313) (1763.3588 5261.9847)
      (1758.9771 5278.8397) (1753.4046 5295.1603) (1746.7939 5310.6565) (1739.313 5325.0687) (1731.1145 5338.1221)
      (1722.3511 5349.5573) (1713.2061 5359.0687) (1703.8168 5366.4122) (1693.771 5371.4046) (1682.7481 5374.2137)
      (1671.0076 5375.1145) (1658.8702 5374.3817) (1646.626 5372.3053) (1634.5802 5369.1298) (1623.0076 5365.145)
      (1612.2137 5360.6107) (1601.5573 5355.0229) (1596.0305 5351.4809) (1594.9313 5356.7786) (1594.0153 5359.9237)
      (1598.7634 5360.6718) (1614.9008 5366.3817) (1625.9542 5375.2672) (1632.2748 5388.5038) (1635.8321 5406.0916)
      (1637.0992 5426.8244) (1636.5496 5449.4656) (1634.687 5472.7939) (1631.9695 5495.5878) (1628.9008 5516.6107)
      (1625.9542 5534.6565) (1622.7481 5550.626) (1618.6565 5566.0916) (1613.8168 5580.7786) (1608.3206 5594.4275)
      (1602.3053 5606.7939) (1595.8779 5617.6183) (1589.1756 5626.626) (1582.2901 5633.5878) (1574.9313 5638.3053)
      (1566.8397 5640.9771) (1558.229 5641.8321) (1549.3282 5641.145) (1540.3511 5639.1756) (1531.5115 5636.1679)
      (1523.0229 5632.3817) (1515.1145 5628.0916) (1507.2977 5622.7939) (1499.1603 5616.0458) (1491.0229 5608.1527)
      (1483.2061 5599.4046) (1476.0153 5590.1374) (1469.771 5580.626) (1466.5191 5574.458) (1465.2672 5575.6641)
      (1450.3817 5587.7863) (1452.0458 5566.8244) (1455.3588 5544.2901) (1460.2748 5520.5344) (1466.7481 5495.9389)
      (1474.7023 5470.8244) (1484.0763 5445.5878) (1494.8092 5420.5954) (1506.8397 5396.1832) (1516.7328 5378.7176)
      (1513.9084 5377.1908) (1504.7786 5371.7405) (1499.6489 5367.374) (1500.0 5364.2748) (1507.2824 5361.7405)
      (1520.7481 5359.2977) (1529.4962 5358.3817) (1534.5802 5350.5802) (1550.1679 5330.1221) (1558.8702 5320.5038)
      (1550.3817 5310.5038) (1543.5878 5300.5496) (1538.9313 5290.9924) (1536.5344 5281.2672) (1536.0458 5270.7939)
      (1537.1756 5259.9695) (1539.6489 5249.1145) (1542.4122 5240.8702) (1537.7405 5244.5344) (1500.916 5271.3282)
      (1466.5038 5294.2901) (1435.1145 5312.9771) (1456.6412 5278.7328) (1481.8931 5242.0458) (1510.4427 5203.4809)
      (1541.8779 5163.6336) (1575.771 5123.0992) (1603.0382 5092.2901) (1598.1221 5090.0305) (1591.1298 5085.4046)
      (1591.6031 5082.1374) (1601.542 5079.4656) (1616.5191 5077.3588) (1641.1298 5051.084) (1620.5954 5064.0458)
      (1577.7557 5089.2519) (1535.7557 5112.1985) (1495.2672 5132.5954) (1456.9466 5150.1527) (1421.4046 5164.5649)
      (1389.313 5175.5725) (1414.3511 5147.6336) (1443.2366 5118.1527) (1475.4809 5087.6031) (1510.6107 5056.458)
      (1548.1527 5025.1908) (1587.6336 4994.2748) (1628.5954 4964.1832) (1665.313 4938.9771) (1635.5573 4949.6489)
      (1591.0076 4963.8931) (1547.0534 4976.3359) (1504.3511 4986.8397) (1463.5115 4995.3282) (1425.2214 5001.6947)
      (1390.0916 5005.8321)
    ))
    ; P2389 -- see feature_dimensions_mm.csv
    ("06_ORNAMENT" 0 (
      (1358.7786 5007.6336) (1358.7786 3740.458) (1358.7786 3679.3893) (1358.7786 3664.1221)
    ))
    ; P2390 -- see feature_dimensions_mm.csv
    ("06_ORNAMENT" 0 (
      (1801.5267 1702.2901) (1813.3282 1704.1527) (1823.9542 1709.5725) (1832.4122 1718.0305) (1837.8321 1728.6565)
      (1839.6947 1740.458) (1837.8321 1752.2595) (1832.4122 1762.8855) (1823.9542 1771.3435) (1813.3282 1776.7634)
      (1801.5267 1778.626)
    ))
    ; P2391 -- see feature_dimensions_mm.csv
    ("06_ORNAMENT" 0 (
      (1801.5267 1536.626) (1804.3664 1533.542) (1812.0763 1528.1069) (1821.2519 1523.9389) (1831.6641 1521.1603)
      (1843.0687 1519.8168) (1855.1756 1519.9542) (1867.6794 1521.5725) (1880.2901 1524.6107) (1892.687 1529.0076)
      (1904.5649 1534.6565) (1915.6336 1541.4198) (1925.6183 1549.1298) (1934.2748 1557.6031) (1941.3893 1566.6107)
      (1946.7786 1575.9389) (1950.3206 1585.374) (1951.9389 1594.6565) (1951.5725 1603.5878) (1949.2366 1611.9237)
      (1944.9924 1619.4656) (1938.9313 1626.0458) (1931.2214 1631.4809) (1922.0458 1635.6336) (1911.6336 1638.4122)
      (1900.2443 1639.7557) (1888.1374 1639.6183) (1875.6183 1638.0153) (1863.0229 1634.9618) (1850.626 1630.5649)
      (1838.7481 1624.916) (1827.6794 1618.1527) (1817.6947 1610.4427) (1809.0382 1601.9847) (1801.9237 1592.9771)
      (1801.5267 1592.2901)
    ))
    ; P2392 -- see feature_dimensions_mm.csv
    ("06_ORNAMENT" 0 (
      (2443.8626 4412.2137) (2259.542 4412.2137) (2229.0076 4412.2137) (2152.6718 4412.2137) (2045.8015 4412.2137)
      (2030.5344 4412.2137) (2030.5344 3832.0611) (2045.8015 3832.0611)
    ))
    ; P2393 -- see feature_dimensions_mm.csv
    ("06_ORNAMENT" 0 (
      (2152.6718 4473.2824) (2259.542 4473.2824) (2449.5725 4473.2824)
    ))
    ; P2394 -- see feature_dimensions_mm.csv
    ("06_ORNAMENT" 0 (
      (2310.8244 4123.6489) (2310.7634 4122.1374) (2311.8473 4097.3282) (2315.084 4072.7023) (2320.458 4048.458)
      (2327.9237 4024.7786) (2337.4351 4001.8321) (2348.9008 3979.8015) (2362.2443 3958.8702) (2377.3588 3939.1603)
      (2394.1374 3920.855) (2412.4427 3904.0763) (2432.1527 3888.9618) (2453.0992 3875.6183) (2475.1145 3864.1527)
      (2498.0611 3854.6412) (2521.7405 3847.1756) (2545.9847 3841.8015) (2570.6107 3838.5649) (2595.4198 3837.4809)
      (2620.229 3838.5649) (2644.855 3841.8015) (2669.0992 3847.1756) (2692.7786 3854.6412) (2715.7252 3864.1527)
      (2737.7557 3875.6183) (2758.687 3888.9618) (2778.3969 3904.0763) (2796.7023 3920.855) (2813.4809 3939.1603)
      (2828.5954 3958.8702) (2841.9389 3979.8015) (2853.4046 4001.8321) (2862.916 4024.7786) (2870.3817 4048.458)
      (2875.7557 4072.7023) (2878.9924 4097.3282) (2880.0763 4122.1374) (2880.0153 4123.6489)
    ))
    ; P2395 -- see feature_dimensions_mm.csv
    ("06_ORNAMENT" 0 (
      (2311.313 4134.5802) (2310.9924 4136.1679) (2307.5115 4141.3588) (2302.3206 4144.8397) (2296.1832 4146.0611)
      (2290.0458 4144.8397) (2284.855 4141.3588) (2281.374 4136.1679) (2280.1527 4130.0305) (2281.374 4123.8931)
      (2284.855 4118.687) (2290.0458 4115.2214) (2296.1832 4114.0) (2302.3206 4115.2214) (2307.5115 4118.687)
      (2310.8244 4123.6489)
    ))
    ; P2396 -- see feature_dimensions_mm.csv
    ("06_ORNAMENT" 0 (
      (2311.313 4134.5802) (2310.8244 4123.6489)
    ))
    ; P2397 -- see feature_dimensions_mm.csv
    ("06_ORNAMENT" 0 (
      (2310.8244 4123.6489) (2310.9924 4123.8931) (2312.2137 4130.0305) (2311.313 4134.5802)
    ))
    ; P2398 -- see feature_dimensions_mm.csv
    ("06_ORNAMENT" 0 (
      (2582.626 4406.229) (2570.6107 4405.7099) (2545.9847 4402.4733) (2521.7405 4397.0992) (2498.0611 4389.6336)
      (2475.1145 4380.1221) (2453.0992 4368.6565) (2432.1527 4355.313) (2412.4427 4340.1985) (2394.1374 4323.4198)
      (2377.3588 4305.1145) (2362.2443 4285.4046) (2348.9008 4264.458) (2337.4351 4242.4427) (2327.9237 4219.4962)
      (2320.458 4195.8168) (2315.084 4171.5725) (2311.8473 4146.9466) (2311.313 4134.5802)
    ))
    ; P2399 -- see feature_dimensions_mm.csv
    ("06_ORNAMENT" 0 (
      (2311.6489 4737.8931) (2310.7634 4717.5573) (2311.8473 4692.7481) (2315.084 4668.1221) (2320.458 4643.8779)
      (2327.9237 4620.1985) (2337.4351 4597.2519) (2348.9008 4575.2214) (2362.2443 4554.2901) (2377.3588 4534.5802)
      (2394.1374 4516.2748) (2412.4427 4499.4962) (2432.1527 4484.3817) (2449.5725 4473.2824)
    ))
    ; P2400 -- see feature_dimensions_mm.csv
    ("06_ORNAMENT" 0 (
      (2311.8626 4742.4885) (2310.9924 4746.855) (2307.5115 4752.0458) (2302.3206 4755.5267) (2296.1832 4756.7481)
      (2290.0458 4755.5267) (2284.855 4752.0458) (2281.374 4746.855) (2280.1527 4740.7176) (2281.374 4734.5802)
      (2284.855 4729.374) (2290.0458 4725.9084) (2296.1832 4724.687) (2302.3206 4725.9084) (2307.5115 4729.374)
      (2310.9924 4734.5802) (2311.6489 4737.8931)
    ))
    ; P2401 -- see feature_dimensions_mm.csv
    ("06_ORNAMENT" 0 (
      (2311.8626 4742.4885) (2311.8473 4742.3664) (2311.6489 4737.8931)
    ))
    ; P2402 -- see feature_dimensions_mm.csv
    ("06_ORNAMENT" 0 (
      (2311.6489 4737.8931) (2312.2137 4740.7176) (2311.8626 4742.4885)
    ))
    ; P2403 -- see feature_dimensions_mm.csv
    ("06_ORNAMENT" 0 (
      (2582.626 5001.6489) (2570.6107 5001.1298) (2545.9847 4997.8931) (2521.7405 4992.5191) (2498.0611 4985.0534)
      (2475.1145 4975.542) (2453.0992 4964.0763) (2432.1527 4950.7328) (2412.4427 4935.6183) (2394.1374 4918.8397)
      (2377.3588 4900.5344) (2362.2443 4880.8244) (2348.9008 4859.8779) (2337.4351 4837.8626) (2327.9237 4814.916)
      (2320.458 4791.2366) (2315.084 4766.9924) (2311.8626 4742.4885)
    ))
    ; P2404 -- see feature_dimensions_mm.csv
    ("06_ORNAMENT" 0 (
      (2319.2824 5330.2901) (2311.1298 5321.2519) (2310.7634 5312.9771) (2311.8473 5288.1679) (2315.084 5263.542)
      (2320.458 5239.2977) (2327.9237 5215.6183) (2337.4351 5192.6718) (2348.9008 5170.6412) (2362.2443 5149.7099)
      (2377.3588 5130.0) (2394.1374 5111.6947) (2412.4427 5094.916) (2432.1527 5079.8015) (2453.0992 5066.458)
      (2475.1145 5054.9924) (2498.0611 5045.4809) (2521.7405 5038.0153) (2545.9847 5032.6412) (2560.1374 5030.7786)
      (2559.2214 5030.1069) (2557.3282 5027.9084) (2556.1374 5025.4809) (2555.7252 5022.9008) (2556.1374 5020.3206)
      (2557.3282 5017.8931) (2559.2214 5015.6947) (2561.6794 5013.8626) (2564.5191 5012.4122) (2567.542 5011.3588)
      (2570.5802 5010.6412) (2573.4198 5010.1985) (2575.9389 5009.8779) (2578.0305 5009.5573) (2579.6641 5009.084)
      (2580.8244 5008.3053) (2581.6031 5007.145) (2582.0763 5005.5115) (2582.3969 5003.4198) (2582.626 5001.6489)
    ))
    ; P2405 -- see feature_dimensions_mm.csv
    ("06_ORNAMENT" 0 (
      (2370.7481 5372.6565) (2353.0687 5359.2824) (2352.3053 5355.8473) (2349.4962 5334.4885) (2348.9924 5323.2061)
      (2347.5115 5320.3664) (2346.3969 5316.7176) (2346.0305 5312.9771) (2346.3969 5309.2366) (2347.5115 5305.5878)
      (2348.9924 5302.7481) (2349.4962 5291.4656) (2352.3053 5270.1069) (2356.9618 5249.084) (2363.4351 5228.5496)
      (2371.6794 5208.6412) (2381.6183 5189.542) (2393.1908 5171.374) (2406.3053 5154.2901) (2413.9389 5145.9695)
      (2414.8855 5142.9008) (2416.687 5139.542) (2419.0687 5136.626) (2421.9847 5134.2443) (2425.3435 5132.4427)
      (2428.4122 5131.4962) (2436.7328 5123.8626) (2453.8168 5110.7481) (2471.9847 5099.1756) (2491.084 5089.2366)
      (2510.9924 5080.9924) (2531.5267 5074.5191) (2552.5496 5069.8626) (2573.9084 5067.0534) (2585.1908 5066.5496)
      (2588.0305 5065.0687) (2591.6794 5063.9542) (2595.4198 5063.5878) (2599.1603 5063.9542) (2602.8092 5065.0687)
      (2605.6489 5066.5496) (2616.9313 5067.0534) (2638.2901 5069.8626) (2659.313 5074.5191) (2679.8473 5080.9924)
      (2699.7557 5089.2366) (2718.855 5099.1756) (2737.0229 5110.7481) (2754.1069 5123.8626) (2762.4275 5131.4962)
      (2765.4962 5132.4427) (2768.855 5134.2443) (2771.771 5136.626) (2774.1527 5139.542) (2775.9542 5142.9008)
      (2776.9008 5145.9695) (2784.5344 5154.2901) (2797.6489 5171.374) (2809.2214 5189.542) (2819.1603 5208.6412)
      (2827.4046 5228.5496) (2833.8779 5249.084) (2838.5344 5270.1069) (2841.3435 5291.4656) (2841.8473 5302.7481)
      (2843.3282 5305.5878) (2844.4427 5309.2366) (2844.8092 5312.9771) (2844.4427 5316.7176) (2843.3282 5320.3664)
      (2841.8473 5323.2061) (2841.3435 5334.4885) (2838.5344 5355.8473) (2833.8779 5376.8702) (2827.4046 5397.4046)
      (2819.1603 5417.313) (2809.2214 5436.4122) (2797.6489 5454.5802) (2784.5344 5471.6641) (2776.9008 5479.9847)
      (2775.9542 5483.0534) (2774.1527 5486.4122) (2771.771 5489.3282) (2768.855 5491.7099) (2765.4962 5493.5115)
      (2762.4275 5494.458) (2754.1069 5502.0916) (2737.0229 5515.2061) (2728.5496 5520.5954)
    ))
    ; P2406 -- see feature_dimensions_mm.csv
    ("06_ORNAMENT" 0 (
      (2380.0 5378.687) (2385.1145 5373.5725) (2392.1374 5370.0) (2399.9237 5368.7634) (2407.7099 5370.0)
      (2414.7328 5373.5725) (2420.3053 5379.145) (2423.8779 5386.1679) (2425.1145 5393.9542) (2423.8779 5401.7405)
      (2422.4427 5404.5649) (2400.9313 5392.3053)
    ))
    ; P2407 -- see feature_dimensions_mm.csv
    ("06_ORNAMENT" 0 (
      (2472.1679 4412.2137) (2443.8626 4412.2137)
    ))
    ; P2408 -- see feature_dimensions_mm.csv
    ("06_ORNAMENT" 0 (
      (2443.8626 4412.2137) (2444.1985 4411.7252) (2444.6718 4410.0916) (2444.9924 4408.0) (2445.313 4405.4809)
      (2445.7557 4402.6412) (2446.4733 4399.6031) (2447.5267 4396.5802) (2448.9771 4393.7405) (2450.8092 4391.2824)
      (2453.0076 4389.3893) (2455.4351 4388.1985) (2458.0153 4387.7863) (2460.5954 4388.1985) (2463.0229 4389.3893)
      (2465.2214 4391.2824) (2467.0534 4393.7405) (2468.5038 4396.5802) (2469.5573 4399.6031) (2470.2748 4402.6412)
      (2470.7176 4405.4809) (2471.0382 4408.0) (2471.3588 4410.0916) (2471.8321 4411.7252) (2472.1679 4412.2137)
    ))
    ; P2409 -- see feature_dimensions_mm.csv
    ("06_ORNAMENT" 0 (
      (2449.5725 4473.2824) (2482.8855 4473.2824)
    ))
    ; P2410 -- see feature_dimensions_mm.csv
    ("06_ORNAMENT" 0 (
      (2456.5649 5422.5496) (2457.4504 5418.1985) (2459.9847 5410.9466) (2463.5573 5403.5725) (2468.1069 5396.2443)
      (2473.5115 5389.145) (2479.6336 5382.4427) (2486.3359 5376.3206) (2493.4351 5370.916) (2500.7634 5366.3664)
      (2508.1374 5362.7939) (2515.3893 5360.2595) (2522.3206 5358.8397) (2528.7786 5358.5802) (2534.5954 5359.4809)
      (2539.6336 5361.5115) (2543.7557 5364.6412) (2546.8855 5368.7634) (2548.916 5373.8015) (2549.8168 5379.6183)
      (2549.5573 5386.0763) (2548.1374 5393.0076) (2545.6031 5400.2595) (2542.0305 5407.6336) (2537.4809 5414.9618)
      (2532.0763 5422.0611) (2525.9542 5428.7634) (2519.2519 5434.8855) (2512.1527 5440.2901) (2504.8244 5444.8397)
      (2504.5649 5444.9618)
    ))
    ; P2411 -- see feature_dimensions_mm.csv
    ("06_ORNAMENT" 0 (
      (2581.2672 4412.2137) (2472.1679 4412.2137)
    ))
    ; P2412 -- see feature_dimensions_mm.csv
    ("06_ORNAMENT" 1 (
      (2482.8855 4473.2824) (2505.5115 4473.2824) (2504.0153 4478.855) (2499.8626 4483.0076) (2494.1985 4484.5191)
      (2488.5344 4483.0076) (2484.3817 4478.855)
    ))
    ; P2413 -- see feature_dimensions_mm.csv
    ("06_ORNAMENT" 0 (
      (2629.5115 4473.2824) (2638.2901 4474.4427) (2659.313 4479.0992) (2679.8473 4485.5725) (2699.7557 4493.8168)
      (2718.855 4503.7557) (2737.0229 4515.3282) (2754.1069 4528.4427) (2762.4275 4536.0763) (2765.4962 4537.0229)
      (2768.855 4538.8244) (2771.771 4541.2061) (2774.1527 4544.1221) (2775.9542 4547.4809) (2776.9008 4550.5496)
      (2784.5344 4558.8702) (2797.6489 4575.9542) (2809.2214 4594.1221) (2819.1603 4613.2214) (2827.4046 4633.1298)
      (2833.8779 4653.6641) (2838.5344 4674.687) (2841.3435 4696.0458) (2841.8473 4707.3282) (2843.3282 4710.1679)
      (2844.4427 4713.8168) (2844.8092 4717.5573) (2844.4427 4721.2977) (2843.3282 4724.9466) (2841.8473 4727.7863)
      (2841.3435 4739.0687) (2838.5344 4760.4275) (2833.8779 4781.4504) (2827.4046 4801.9847) (2819.1603 4821.8931)
      (2809.2214 4840.9924) (2797.6489 4859.1603) (2784.5344 4876.2443) (2776.9008 4884.5649) (2775.9542 4887.6336)
      (2774.1527 4890.9924) (2771.771 4893.9084) (2768.855 4896.2901) (2765.4962 4898.0916) (2762.4275 4899.0382)
      (2754.1069 4906.6718) (2737.0229 4919.7863) (2718.855 4931.3588) (2699.7557 4941.2977) (2679.8473 4949.542)
      (2659.313 4956.0153) (2638.2901 4960.6718) (2616.9313 4963.4809) (2605.6489 4963.9847) (2602.8092 4965.4656)
      (2599.1603 4966.5802) (2595.4198 4966.9466) (2591.6794 4966.5802) (2588.0305 4965.4656) (2585.1908 4963.9847)
      (2573.9084 4963.4809) (2552.5496 4960.6718) (2531.5267 4956.0153) (2510.9924 4949.542) (2491.084 4941.2977)
      (2471.9847 4931.3588) (2453.8168 4919.7863) (2436.7328 4906.6718) (2428.4122 4899.0382) (2425.3435 4898.0916)
      (2421.9847 4896.2901) (2419.0687 4893.9084) (2416.687 4890.9924) (2414.8855 4887.6336) (2413.9389 4884.5649)
      (2406.3053 4876.2443) (2393.1908 4859.1603) (2381.6183 4840.9924) (2371.6794 4821.8931) (2363.4351 4801.9847)
      (2356.9618 4781.4504) (2352.3053 4760.4275) (2349.4962 4739.0687) (2348.9924 4727.7863) (2347.5115 4724.9466)
      (2346.3969 4721.2977) (2346.0305 4717.5573) (2346.3969 4713.8168) (2347.5115 4710.1679) (2348.9924 4707.3282)
      (2349.4962 4696.0458) (2352.3053 4674.687) (2356.9618 4653.6641) (2363.4351 4633.1298) (2371.6794 4613.2214)
      (2381.6183 4594.1221) (2393.1908 4575.9542) (2406.3053 4558.8702) (2413.9389 4550.5496) (2414.8855 4547.4809)
      (2416.687 4544.1221) (2419.0687 4541.2061) (2421.9847 4538.8244) (2425.3435 4537.0229) (2428.4122 4536.0763)
      (2436.7328 4528.4427) (2453.8168 4515.3282) (2471.9847 4503.7557) (2491.084 4493.8168) (2510.9924 4485.5725)
      (2531.5267 4479.0992) (2552.5496 4474.4427) (2561.3282 4473.2824)
    ))
    ; P2414 -- see feature_dimensions_mm.csv
    ("06_ORNAMENT" 0 (
      (2566.0305 5469.4046) (2564.2748 5461.8779) (2563.0687 5453.0382) (2562.6718 5443.9695) (2563.0687 5434.9008)
      (2564.2748 5426.0611) (2566.2443 5417.6641) (2568.9313 5409.9084) (2572.2595 5403.0076) (2576.1679 5397.0992)
      (2580.5496 5392.3511) (2585.2977 5388.8702) (2590.2901 5386.7481) (2595.4198 5386.0305) (2600.5496 5386.7481)
      (2605.542 5388.8702) (2610.2901 5392.3511) (2614.6718 5397.0992) (2618.5802 5403.0076) (2621.9084 5409.9084)
      (2624.5954 5417.6641) (2626.5649 5426.0611) (2627.771 5434.9008) (2628.1679 5443.9695) (2627.771 5453.0382)
      (2626.5649 5461.8779) (2624.5954 5470.2748) (2621.9084 5478.0305) (2618.5802 5484.9313) (2616.9618 5487.374)
      (2582.0153 5475.3893)
    ))
    ; P2415 -- see feature_dimensions_mm.csv
    ("06_ORNAMENT" 0 (
      (2609.5725 4412.2137) (2581.2672 4412.2137)
    ))
    ; P2416 -- see feature_dimensions_mm.csv
    ("06_ORNAMENT" 0 (
      (2581.2672 4412.2137) (2581.6031 4411.7252) (2582.0763 4410.0916) (2582.3969 4408.0) (2582.626 4406.229)
    ))
    ; P2417 -- see feature_dimensions_mm.csv
    ("06_ORNAMENT" 0 (
      (2595.4198 4528.626) (2591.6794 4528.2595) (2588.0305 4527.145) (2584.5496 4525.3282) (2581.3588 4522.855)
      (2578.5038 4519.771) (2576.0611 4516.1679) (2574.0916 4512.1221) (2572.6565 4507.7405) (2571.7863 4503.1298)
      (2571.4962 4498.3969) (2571.7863 4493.6641) (2572.6565 4489.0534) (2574.0916 4484.6718) (2576.0611 4480.626)
      (2578.5038 4477.0229) (2581.3588 4473.9389) (2582.1985 4473.2824)
    ))
    ; P2418 -- see feature_dimensions_mm.csv
    ("06_ORNAMENT" 0 (
      (2582.626 5001.6489) (2582.7176 5000.9008) (2583.1603 4998.0611) (2583.8779 4995.0229) (2584.9313 4992.0)
      (2586.3817 4989.1603) (2586.6565 4988.7786) (2585.6031 4987.7252) (2584.0916 4982.0611) (2585.6031 4976.3969)
      (2589.7557 4972.2443) (2595.4198 4970.7176) (2601.084 4972.2443) (2605.2366 4976.3969) (2606.7634 4982.0611)
      (2605.2366 4987.7252) (2604.1832 4988.7786) (2604.458 4989.1603) (2605.9084 4992.0) (2606.9618 4995.0229)
      (2607.6794 4998.0611) (2608.1221 5000.9008) (2608.2137 5001.6489)
    ))
    ; P2419 -- see feature_dimensions_mm.csv
    ("06_ORNAMENT" 0 (
      (2608.2137 5001.6489) (2595.4198 5002.2137) (2582.626 5001.6489)
    ))
    ; P2420 -- see feature_dimensions_mm.csv
    ("06_ORNAMENT" 0 (
      (2582.626 4406.229) (2582.7176 4405.4809) (2583.1603 4402.6412) (2583.8779 4399.6031) (2584.9313 4396.5802)
      (2586.3817 4393.7405) (2586.6565 4393.3588) (2585.6031 4392.3053) (2584.0916 4386.6412) (2585.6031 4380.9771)
      (2589.7557 4376.8244) (2595.4198 4375.2977) (2601.084 4376.8244) (2605.2366 4380.9771) (2606.7634 4386.6412)
      (2605.2366 4392.3053) (2604.1832 4393.3588) (2604.458 4393.7405) (2605.9084 4396.5802) (2606.9618 4399.6031)
      (2607.6794 4402.6412) (2608.1221 4405.4809) (2608.2137 4406.229)
    ))
    ; P2421 -- see feature_dimensions_mm.csv
    ("06_ORNAMENT" 0 (
      (2608.2137 4406.229) (2595.4198 4406.7939) (2582.626 4406.229)
    ))
    ; P2422 -- see feature_dimensions_mm.csv
    ("06_ORNAMENT" 0 (
      (2608.6412 4473.2824) (2609.4809 4473.9389) (2612.3359 4477.0229) (2614.7786 4480.626) (2616.7481 4484.6718)
      (2618.1832 4489.0534) (2619.0534 4493.6641) (2619.3588 4498.3969) (2619.0534 4503.1298) (2618.1832 4507.7405)
      (2616.7481 4512.1221) (2614.7786 4516.1679) (2612.3359 4519.771) (2609.4809 4522.855) (2606.2901 4525.3282)
      (2602.8092 4527.145) (2599.1603 4528.2595) (2595.4198 4528.626)
    ))
    ; P2423 -- see feature_dimensions_mm.csv
    ("06_ORNAMENT" 1 (
      (2595.4198 4528.626) (2600.5496 4529.3435) (2605.542 4531.4656) (2610.2901 4534.9466) (2614.6718 4539.6947)
      (2618.5802 4545.6031) (2621.9084 4552.5038) (2624.5954 4560.2595) (2626.5649 4568.6565) (2627.771 4577.4962)
      (2628.1679 4586.5649) (2627.771 4595.6336) (2626.5649 4604.4733) (2624.5954 4612.8702) (2621.9084 4620.626)
      (2618.5802 4627.5267) (2614.6718 4633.4351) (2610.2901 4638.1832) (2605.542 4641.6641) (2600.5496 4643.7863)
      (2595.4198 4644.5038) (2590.2901 4643.7863) (2585.2977 4641.6641) (2580.5496 4638.1832) (2576.1679 4633.4351)
      (2572.2595 4627.5267) (2568.9313 4620.626) (2566.2443 4612.8702) (2564.2748 4604.4733) (2563.0687 4595.6336)
      (2562.6718 4586.5649) (2563.0687 4577.4962) (2564.2748 4568.6565) (2566.2443 4560.2595) (2568.9313 4552.5038)
      (2572.2595 4545.6031) (2576.1679 4539.6947) (2580.5496 4534.9466) (2585.2977 4531.4656) (2590.2901 4529.3435)
    ))
    ; P2424 -- see feature_dimensions_mm.csv
    ("06_ORNAMENT" 0 (
      (2878.9771 4742.4885) (2875.7557 4766.9924) (2870.3817 4791.2366) (2862.916 4814.916) (2853.4046 4837.8626)
      (2841.9389 4859.8779) (2828.5954 4880.8244) (2813.4809 4900.5344) (2796.7023 4918.8397) (2778.3969 4935.6183)
      (2758.687 4950.7328) (2737.7557 4964.0763) (2715.7252 4975.542) (2692.7786 4985.0534) (2669.0992 4992.5191)
      (2644.855 4997.8931) (2620.229 5001.1298) (2608.2137 5001.6489)
    ))
    ; P2425 -- see feature_dimensions_mm.csv
    ("06_ORNAMENT" 0 (
      (2608.2137 5001.6489) (2608.4427 5003.4198) (2608.7634 5005.5115) (2609.2366 5007.145) (2610.0153 5008.3053)
      (2611.1756 5009.084) (2612.8092 5009.5573) (2614.9008 5009.8779) (2617.4198 5010.1985) (2620.2595 5010.6412)
      (2623.2977 5011.3588) (2626.3206 5012.4122) (2629.1603 5013.8626) (2631.6183 5015.6947) (2633.5115 5017.8931)
      (2634.7023 5020.3206) (2635.1145 5022.9008) (2634.7023 5025.4809) (2633.5115 5027.9084) (2631.6183 5030.1069)
      (2630.7023 5030.7786) (2644.855 5032.6412) (2669.0992 5038.0153) (2692.7786 5045.4809) (2715.7252 5054.9924)
      (2737.7557 5066.458) (2758.687 5079.8015) (2778.3969 5094.916) (2796.7023 5111.6947) (2813.4809 5130.0)
      (2828.5954 5149.7099) (2841.9389 5170.6412) (2853.4046 5192.6718) (2862.916 5215.6183) (2870.3817 5239.2977)
      (2875.7557 5263.542) (2878.9924 5288.1679) (2880.0763 5312.9771) (2878.9924 5337.7863) (2875.7557 5362.4122)
      (2870.3817 5386.6565) (2862.916 5410.3359) (2853.4046 5433.2824) (2841.9389 5455.2977) (2828.5954 5476.2443)
      (2813.4809 5495.9542) (2796.7023 5514.2595) (2778.3969 5531.0382) (2776.1069 5532.7786)
    ))
    ; P2426 -- see feature_dimensions_mm.csv
    ("06_ORNAMENT" 0 (
      (2879.5267 4134.5802) (2878.9924 4146.9466) (2875.7557 4171.5725) (2870.3817 4195.8168) (2862.916 4219.4962)
      (2853.4046 4242.4427) (2841.9389 4264.458) (2828.5954 4285.4046) (2813.4809 4305.1145) (2796.7023 4323.4198)
      (2778.3969 4340.1985) (2758.687 4355.313) (2737.7557 4368.6565) (2715.7252 4380.1221) (2692.7786 4389.6336)
      (2669.0992 4397.0992) (2644.855 4402.4733) (2620.229 4405.7099) (2608.2137 4406.229)
    ))
    ; P2427 -- see feature_dimensions_mm.csv
    ("06_ORNAMENT" 0 (
      (2608.2137 4406.229) (2608.4427 4408.0) (2608.7634 4410.0916) (2609.2366 4411.7252) (2609.5725 4412.2137)
    ))
    ; P2428 -- see feature_dimensions_mm.csv
    ("06_ORNAMENT" 0 (
      (2718.6718 4412.2137) (2609.5725 4412.2137)
    ))
    ; P2429 -- see feature_dimensions_mm.csv
    ("06_ORNAMENT" 0 (
      (2661.771 5501.6641) (2653.2977 5498.9924) (2656.0153 5493.6641) (2661.5878 5488.0916) (2668.6107 5484.5191)
      (2676.3969 5483.2824) (2684.1832 5484.5191) (2691.2061 5488.0916) (2696.7786 5493.6641) (2700.3511 5500.687)
      (2701.5878 5508.4733) (2700.855 5513.084) (2701.771 5513.3435) (2728.5496 5520.5954)
    ))
    ; P2430 -- see feature_dimensions_mm.csv
    ("06_ORNAMENT" 0 (
      (2707.9542 4473.2824) (2706.458 4478.855) (2702.3053 4483.0076) (2696.6412 4484.5191) (2690.9771 4483.0076)
      (2686.8244 4478.855) (2685.3282 4473.2824)
    ))
    ; P2431 -- see feature_dimensions_mm.csv
    ("06_ORNAMENT" 0 (
      (2708.7634 1928.2748) (2702.1221 1955.0229) (2697.8321 1956.9771) (2687.4198 1959.7557) (2676.0153 1961.0992)
      (2663.9084 1960.9618) (2651.4046 1959.3435) (2638.7939 1956.3053) (2626.3969 1951.9084) (2614.5191 1946.2595)
      (2603.4504 1939.4962) (2593.4656 1931.7863) (2584.8092 1923.313) (2577.6947 1914.3053) (2572.3053 1904.9771)
      (2568.7634 1895.542) (2567.145 1886.2595) (2567.5115 1877.3282) (2569.8473 1868.9924) (2574.0916 1861.4504)
      (2580.1527 1854.8702) (2587.8626 1849.4351) (2597.0382 1845.2824) (2607.4504 1842.5038) (2618.855 1841.1603)
      (2630.9466 1841.2977) (2643.4656 1842.9008) (2656.0611 1845.9542) (2668.458 1850.3511) (2680.3359 1856.0)
      (2691.4046 1862.7634) (2701.3893 1870.4733) (2710.0458 1878.9313) (2715.2061 1885.4809) (2713.6336 1900.4733)
    ))
    ; P2432 -- see feature_dimensions_mm.csv
    ("06_ORNAMENT" 0 (
      (2717.5573 1778.626) (2705.7557 1776.7634) (2695.1298 1771.3435) (2686.6718 1762.8855) (2681.2519 1752.2595)
      (2679.3893 1740.458) (2681.2519 1728.6565) (2686.6718 1718.0305) (2695.1298 1709.5725) (2705.7557 1704.1527)
      (2717.5573 1702.2901)
    ))
    ; P2433 -- see feature_dimensions_mm.csv
    ("06_ORNAMENT" 0 (
      (2717.5573 1592.2901) (2717.1603 1592.9771) (2710.0458 1601.9847) (2701.3893 1610.4427) (2691.4046 1618.1527)
      (2680.3359 1624.916) (2668.458 1630.5649) (2656.0611 1634.9618) (2643.4656 1638.0153) (2630.9466 1639.6183)
      (2618.855 1639.7557) (2607.4504 1638.4122) (2597.0382 1635.6336) (2587.8626 1631.4809) (2580.1527 1626.0458)
      (2574.0916 1619.4656) (2569.8473 1611.9237) (2567.5115 1603.5878) (2567.145 1594.6565) (2568.7634 1585.374)
      (2572.3053 1575.9389) (2577.6947 1566.6107) (2584.8092 1557.6031) (2593.4656 1549.1298) (2603.4504 1541.4198)
      (2614.5191 1534.6565) (2626.3969 1529.0076) (2638.7939 1524.6107) (2651.4046 1521.5725) (2663.9084 1519.9542)
      (2676.0153 1519.8168) (2687.4198 1521.1603) (2697.8321 1523.9389) (2707.0076 1528.1069) (2714.7176 1533.542)
      (2717.5573 1536.626)
    ))
    ; P2434 -- see feature_dimensions_mm.csv
    ("06_ORNAMENT" 0 (
      (2746.9771 4412.2137) (2718.6718 4412.2137)
    ))
    ; P2435 -- see feature_dimensions_mm.csv
    ("06_ORNAMENT" 0 (
      (2718.6718 4412.2137) (2719.0076 4411.7252) (2719.4809 4410.0916) (2719.8015 4408.0) (2720.1221 4405.4809)
      (2720.5649 4402.6412) (2721.2824 4399.6031) (2722.3359 4396.5802) (2723.7863 4393.7405) (2725.6183 4391.2824)
      (2727.8168 4389.3893) (2730.2443 4388.1985) (2732.8244 4387.7863) (2735.4046 4388.1985) (2737.8321 4389.3893)
      (2740.0305 4391.2824) (2741.8626 4393.7405) (2743.313 4396.5802) (2744.3664 4399.6031) (2745.084 4402.6412)
      (2745.5267 4405.4809) (2745.8473 4408.0) (2746.1679 4410.0916) (2746.6412 4411.7252) (2746.9771 4412.2137)
    ))
    ; P2436 -- see feature_dimensions_mm.csv
    ("06_ORNAMENT" 0 (
      (2741.374 5524.0611) (2728.5496 5520.5954)
    ))
    ; P2437 -- see feature_dimensions_mm.csv
    ("06_ORNAMENT" 0 (
      (2741.2672 4473.2824) (2758.687 4484.3817) (2778.3969 4499.4962) (2796.7023 4516.2748) (2813.4809 4534.5802)
      (2828.5954 4554.2901) (2841.9389 4575.2214) (2853.4046 4597.2519) (2862.916 4620.1985) (2870.3817 4643.8779)
      (2875.7557 4668.1221) (2878.9924 4692.7481) (2880.0763 4717.5573) (2879.1908 4737.8931)
    ))
    ; P2438 -- see feature_dimensions_mm.csv
    ("06_ORNAMENT" 0 (
      (2961.8321 3832.0611) (2961.8321 4412.2137) (2938.9313 4412.2137) (2746.9771 4412.2137)
    ))
    ; P2439 -- see feature_dimensions_mm.csv
    ("06_ORNAMENT" 0 (
      (2897.7099 5938.9313) (2880.0153 5952.7328) (2860.0763 5965.7557) (2838.2443 5977.9847) (2814.9008 5989.3435)
      (2790.4275 5999.8015) (2765.1908 6009.313) (2739.542 6017.8321) (2713.8779 6025.313) (2688.5649 6031.7099)
      (2663.9695 6036.9618) (2640.458 6041.0534) (2618.3969 6043.9237) (2598.1679 6045.5115) (2580.1527 6045.8015)
      (2596.5344 6034.5038) (2615.084 6023.0534) (2635.5267 6011.6183) (2657.5267 6000.3817) (2680.8092 5989.542)
      (2705.0534 5979.2519) (2729.9847 5969.7099) (2755.2672 5961.084) (2780.6107 5953.5725) (2805.7252 5947.3435)
      (2830.2901 5942.5954) (2854.0153 5939.4809) (2863.6794 5938.9313)
    ))
    ; P2440 -- see feature_dimensions_mm.csv
    ("06_ORNAMENT" 0 (
      (2879.1908 4737.8931) (2878.9924 4742.3664) (2878.9771 4742.4885)
    ))
    ; P2441 -- see feature_dimensions_mm.csv
    ("06_ORNAMENT" 0 (
      (2878.9771 4742.4885) (2878.626 4740.7176) (2879.1908 4737.8931)
    ))
    ; P2442 -- see feature_dimensions_mm.csv
    ("06_ORNAMENT" 0 (
      (2879.1908 4737.8931) (2879.8473 4734.5802) (2883.3282 4729.374) (2888.5191 4725.9084) (2894.6565 4724.687)
      (2900.7939 4725.9084) (2905.9847 4729.374) (2909.4656 4734.5802) (2910.687 4740.7176) (2909.4656 4746.855)
      (2905.9847 4752.0458) (2900.7939 4755.5267) (2894.6565 4756.7481) (2888.5191 4755.5267) (2883.3282 4752.0458)
      (2879.8473 4746.855) (2878.9771 4742.4885)
    ))
    ; P2443 -- see feature_dimensions_mm.csv
    ("06_ORNAMENT" 0 (
      (2880.0153 4123.6489) (2879.5267 4134.5802)
    ))
    ; P2444 -- see feature_dimensions_mm.csv
    ("06_ORNAMENT" 0 (
      (2879.5267 4134.5802) (2878.626 4130.0305) (2879.8473 4123.8931) (2880.0153 4123.6489)
    ))
    ; P2445 -- see feature_dimensions_mm.csv
    ("06_ORNAMENT" 0 (
      (2880.0153 4123.6489) (2883.3282 4118.687) (2888.5191 4115.2214) (2894.6565 4114.0) (2900.7939 4115.2214)
      (2905.9847 4118.687) (2909.4656 4123.8931) (2910.687 4130.0305) (2909.4656 4136.1679) (2905.9847 4141.3588)
      (2900.7939 4144.8397) (2894.6565 4146.0611) (2888.5191 4144.8397) (2883.3282 4141.3588) (2879.8473 4136.1679)
      (2879.5267 4134.5802)
    ))
    ; P2446 -- see feature_dimensions_mm.csv
    ("06_ORNAMENT" 0 (
      (3074.1832 4123.6489) (3074.1221 4122.1374) (3075.2061 4097.3282) (3078.4427 4072.7023) (3083.8168 4048.458)
      (3091.2824 4024.7786) (3100.7939 4001.8321) (3112.2595 3979.8015) (3125.6031 3958.8702) (3140.7176 3939.1603)
      (3157.4962 3920.855) (3175.8015 3904.0763) (3195.5115 3888.9618) (3216.458 3875.6183) (3238.4733 3864.1527)
      (3261.4198 3854.6412) (3285.0992 3847.1756) (3309.3435 3841.8015) (3333.9695 3838.5649) (3358.7786 3837.4809)
      (3383.5878 3838.5649) (3408.2137 3841.8015) (3432.458 3847.1756) (3456.1374 3854.6412) (3479.084 3864.1527)
      (3501.1145 3875.6183) (3522.0458 3888.9618) (3541.7557 3904.0763) (3560.0611 3920.855) (3576.8397 3939.1603)
      (3591.9542 3958.8702) (3605.2977 3979.8015) (3616.7634 4001.8321) (3626.2748 4024.7786) (3633.7405 4048.458)
      (3639.1145 4072.7023) (3642.3511 4097.3282) (3643.4351 4122.1374) (3643.374 4123.6489)
    ))
    ; P2447 -- see feature_dimensions_mm.csv
    ("06_ORNAMENT" 0 (
      (3074.6718 4134.5802) (3074.3511 4136.1679) (3070.8702 4141.3588) (3065.6794 4144.8397) (3059.542 4146.0611)
      (3053.4046 4144.8397) (3048.2137 4141.3588) (3044.7328 4136.1679) (3043.5115 4130.0305) (3044.7328 4123.8931)
      (3048.2137 4118.687) (3053.4046 4115.2214) (3059.542 4114.0) (3065.6794 4115.2214) (3070.8702 4118.687)
      (3074.1832 4123.6489)
    ))
    ; P2448 -- see feature_dimensions_mm.csv
    ("06_ORNAMENT" 0 (
      (3074.6718 4134.5802) (3074.1832 4123.6489)
    ))
    ; P2449 -- see feature_dimensions_mm.csv
    ("06_ORNAMENT" 0 (
      (3074.1832 4123.6489) (3074.3511 4123.8931) (3075.5725 4130.0305) (3074.6718 4134.5802)
    ))
    ; P2450 -- see feature_dimensions_mm.csv
    ("06_ORNAMENT" 0 (
      (3345.9847 4406.229) (3333.9695 4405.7099) (3309.3435 4402.4733) (3285.0992 4397.0992) (3261.4198 4389.6336)
      (3238.4733 4380.1221) (3216.458 4368.6565) (3195.5115 4355.313) (3175.8015 4340.1985) (3157.4962 4323.4198)
      (3140.7176 4305.1145) (3125.6031 4285.4046) (3112.2595 4264.458) (3100.7939 4242.4427) (3091.2824 4219.4962)
      (3083.8168 4195.8168) (3078.4427 4171.5725) (3075.2061 4146.9466) (3074.6718 4134.5802)
    ))
    ; P2451 -- see feature_dimensions_mm.csv
    ("06_ORNAMENT" 0 (
      (3075.0076 4737.8931) (3074.1221 4717.5573) (3075.2061 4692.7481) (3078.4427 4668.1221) (3083.8168 4643.8779)
      (3091.2824 4620.1985) (3100.7939 4597.2519) (3112.2595 4575.2214) (3125.6031 4554.2901) (3140.7176 4534.5802)
      (3157.4962 4516.2748) (3175.8015 4499.4962) (3195.5115 4484.3817) (3212.9313 4473.2824)
    ))
    ; P2452 -- see feature_dimensions_mm.csv
    ("06_ORNAMENT" 0 (
      (3075.2214 4742.4885) (3074.3511 4746.855) (3070.8702 4752.0458) (3065.6794 4755.5267) (3059.542 4756.7481)
      (3053.4046 4755.5267) (3048.2137 4752.0458) (3044.7328 4746.855) (3043.5115 4740.7176) (3044.7328 4734.5802)
      (3048.2137 4729.374) (3053.4046 4725.9084) (3059.542 4724.687) (3065.6794 4725.9084) (3070.8702 4729.374)
      (3074.3511 4734.5802) (3075.0076 4737.8931)
    ))
    ; P2453 -- see feature_dimensions_mm.csv
    ("06_ORNAMENT" 0 (
      (3075.2214 4742.4885) (3075.2061 4742.3664) (3075.0076 4737.8931)
    ))
    ; P2454 -- see feature_dimensions_mm.csv
    ("06_ORNAMENT" 0 (
      (3075.0076 4737.8931) (3075.5725 4740.7176) (3075.2214 4742.4885)
    ))
    ; P2455 -- see feature_dimensions_mm.csv
    ("06_ORNAMENT" 0 (
      (3345.9847 5001.6489) (3333.9695 5001.1298) (3309.3435 4997.8931) (3285.0992 4992.5191) (3261.4198 4985.0534)
      (3238.4733 4975.542) (3216.458 4964.0763) (3195.5115 4950.7328) (3175.8015 4935.6183) (3157.4962 4918.8397)
      (3140.7176 4900.5344) (3125.6031 4880.8244) (3112.2595 4859.8779) (3100.7939 4837.8626) (3091.2824 4814.916)
      (3083.8168 4791.2366) (3078.4427 4766.9924) (3075.2214 4742.4885)
    ))
    ; P2456 -- see feature_dimensions_mm.csv
    ("06_ORNAMENT" 0 (
      (3178.0916 5532.7786) (3175.8015 5531.0382) (3157.4962 5514.2595) (3140.7176 5495.9542) (3125.6031 5476.2443)
      (3112.2595 5455.2977) (3100.7939 5433.2824) (3091.2824 5410.3359) (3083.8168 5386.6565) (3078.4427 5362.4122)
      (3075.2061 5337.7863) (3074.1221 5312.9771) (3075.2061 5288.1679) (3078.4427 5263.542) (3083.8168 5239.2977)
      (3091.2824 5215.6183) (3100.7939 5192.6718) (3112.2595 5170.6412) (3125.6031 5149.7099) (3140.7176 5130.0)
      (3157.4962 5111.6947) (3175.8015 5094.916) (3195.5115 5079.8015) (3216.458 5066.458) (3238.4733 5054.9924)
      (3261.4198 5045.4809) (3285.0992 5038.0153) (3309.3435 5032.6412) (3323.4962 5030.7786) (3322.5802 5030.1069)
      (3320.687 5027.9084) (3319.4962 5025.4809) (3319.084 5022.9008) (3319.4962 5020.3206) (3320.687 5017.8931)
      (3322.5802 5015.6947) (3325.0382 5013.8626) (3327.8779 5012.4122) (3330.9008 5011.3588) (3333.9389 5010.6412)
      (3336.7786 5010.1985) (3339.2977 5009.8779) (3341.3893 5009.5573) (3343.0229 5009.084) (3344.1832 5008.3053)
      (3344.9618 5007.145) (3345.4351 5005.5115) (3345.7557 5003.4198) (3345.9847 5001.6489)
    ))
    ; P2457 -- see feature_dimensions_mm.csv
    ("06_ORNAMENT" 0 (
      (3207.2214 4412.2137) (3207.5573 4411.7252) (3208.0305 4410.0916) (3208.3511 4408.0) (3208.6718 4405.4809)
      (3209.1145 4402.6412) (3209.8321 4399.6031) (3210.8855 4396.5802) (3212.3359 4393.7405) (3214.1679 4391.2824)
      (3216.3664 4389.3893) (3218.7939 4388.1985) (3221.374 4387.7863) (3223.9542 4388.1985) (3226.3817 4389.3893)
      (3228.5802 4391.2824) (3230.4122 4393.7405) (3231.8626 4396.5802) (3232.916 4399.6031) (3233.6336 4402.6412)
      (3234.0763 4405.4809) (3234.3969 4408.0) (3234.7176 4410.0916) (3235.1908 4411.7252) (3235.5267 4412.2137)
    ))
    ; P2458 -- see feature_dimensions_mm.csv
    ("06_ORNAMENT" 0 (
      (3212.8244 5524.0611) (3225.6489 5520.5954) (3217.1756 5515.2061) (3200.0916 5502.0916) (3191.771 5494.458)
      (3188.7023 5493.5115) (3185.3435 5491.7099) (3182.4275 5489.3282) (3180.0458 5486.4122) (3178.2443 5483.0534)
      (3177.2977 5479.9847) (3169.6641 5471.6641) (3156.5496 5454.5802) (3144.9771 5436.4122) (3135.0382 5417.313)
      (3126.7939 5397.4046) (3120.3206 5376.8702) (3115.6641 5355.8473) (3112.855 5334.4885) (3112.3511 5323.2061)
      (3110.8702 5320.3664) (3109.7557 5316.7176) (3109.3893 5312.9771) (3109.7557 5309.2366) (3110.8702 5305.5878)
      (3112.3511 5302.7481) (3112.855 5291.4656) (3115.6641 5270.1069) (3120.3206 5249.084) (3126.7939 5228.5496)
      (3135.0382 5208.6412) (3144.9771 5189.542) (3156.5496 5171.374) (3169.6641 5154.2901) (3177.2977 5145.9695)
      (3178.2443 5142.9008) (3180.0458 5139.542) (3182.4275 5136.626) (3185.3435 5134.2443) (3188.7023 5132.4427)
      (3191.771 5131.4962) (3200.0916 5123.8626) (3217.1756 5110.7481) (3235.3435 5099.1756) (3254.4427 5089.2366)
      (3274.3511 5080.9924) (3294.8855 5074.5191) (3315.9084 5069.8626) (3337.2672 5067.0534) (3348.5496 5066.5496)
      (3351.3893 5065.0687) (3355.0382 5063.9542) (3358.7786 5063.5878) (3362.5191 5063.9542) (3366.1679 5065.0687)
      (3369.0076 5066.5496) (3380.2901 5067.0534) (3401.6489 5069.8626) (3422.6718 5074.5191) (3443.2061 5080.9924)
      (3463.1145 5089.2366) (3482.2137 5099.1756) (3500.3817 5110.7481) (3517.4656 5123.8626) (3525.7863 5131.4962)
      (3528.855 5132.4427) (3532.2137 5134.2443) (3535.1298 5136.626) (3537.5115 5139.542) (3539.313 5142.9008)
      (3540.2595 5145.9695) (3547.8931 5154.2901) (3561.0076 5171.374) (3572.5802 5189.542) (3582.5191 5208.6412)
      (3590.7634 5228.5496) (3597.2366 5249.084) (3601.8931 5270.1069) (3604.7023 5291.4656) (3605.2061 5302.7481)
      (3606.687 5305.5878) (3607.8015 5309.2366) (3608.1679 5312.9771) (3607.8015 5316.7176) (3606.687 5320.3664)
      (3605.2061 5323.2061) (3604.7023 5334.4885) (3601.8931 5355.8473) (3601.1298 5359.2824) (3583.4656 5372.6565)
    ))
    ; P2459 -- see feature_dimensions_mm.csv
    ("06_ORNAMENT" 0 (
      (3268.8702 4473.2824) (3267.374 4478.855) (3263.2214 4483.0076) (3257.5573 4484.5191) (3251.8931 4483.0076)
      (3247.7405 4478.855) (3246.2443 4473.2824)
    ))
    ; P2460 -- see feature_dimensions_mm.csv
    ("06_ORNAMENT" 0 (
      (3253.3435 5513.084) (3252.4275 5513.3435)
    ))
    ; P2461 -- see feature_dimensions_mm.csv
    ("06_ORNAMENT" 0 (
      (3300.9008 5498.9924) (3292.4275 5501.6641) (3253.3435 5513.084)
    ))
    ; P2462 -- see feature_dimensions_mm.csv
    ("06_ORNAMENT" 0 (
      (3253.3435 5513.084) (3252.6107 5508.4733) (3253.8473 5500.687) (3257.4198 5493.6641) (3262.9924 5488.0916)
      (3270.0153 5484.5191) (3277.8015 5483.2824) (3285.5878 5484.5191) (3292.6107 5488.0916) (3298.1832 5493.6641)
      (3300.9008 5498.9924)
    ))
    ; P2463 -- see feature_dimensions_mm.csv
    ("06_ORNAMENT" 0 (
      (3337.2366 5487.374) (3332.4733 5489.0229) (3300.9008 5498.9924)
    ))
    ; P2464 -- see feature_dimensions_mm.csv
    ("06_ORNAMENT" 0 (
      (3392.8702 4473.2824) (3401.6489 4474.4427) (3422.6718 4479.0992) (3443.2061 4485.5725) (3463.1145 4493.8168)
      (3482.2137 4503.7557) (3500.3817 4515.3282) (3517.4656 4528.4427) (3525.7863 4536.0763) (3528.855 4537.0229)
      (3532.2137 4538.8244) (3535.1298 4541.2061) (3537.5115 4544.1221) (3539.313 4547.4809) (3540.2595 4550.5496)
      (3547.8931 4558.8702) (3561.0076 4575.9542) (3572.5802 4594.1221) (3582.5191 4613.2214) (3590.7634 4633.1298)
      (3597.2366 4653.6641) (3601.8931 4674.687) (3604.7023 4696.0458) (3605.2061 4707.3282) (3606.687 4710.1679)
      (3607.8015 4713.8168) (3608.1679 4717.5573) (3607.8015 4721.2977) (3606.687 4724.9466) (3605.2061 4727.7863)
      (3604.7023 4739.0687) (3601.8931 4760.4275) (3597.2366 4781.4504) (3590.7634 4801.9847) (3582.5191 4821.8931)
      (3572.5802 4840.9924) (3561.0076 4859.1603) (3547.8931 4876.2443) (3540.2595 4884.5649) (3539.313 4887.6336)
      (3537.5115 4890.9924) (3535.1298 4893.9084) (3532.2137 4896.2901) (3528.855 4898.0916) (3525.7863 4899.0382)
      (3517.4656 4906.6718) (3500.3817 4919.7863) (3482.2137 4931.3588) (3463.1145 4941.2977) (3443.2061 4949.542)
      (3422.6718 4956.0153) (3401.6489 4960.6718) (3380.2901 4963.4809) (3369.0076 4963.9847) (3366.1679 4965.4656)
      (3362.5191 4966.5802) (3358.7786 4966.9466) (3355.0382 4966.5802) (3351.3893 4965.4656) (3348.5496 4963.9847)
      (3337.2672 4963.4809) (3315.9084 4960.6718) (3294.8855 4956.0153) (3274.3511 4949.542) (3254.4427 4941.2977)
      (3235.3435 4931.3588) (3217.1756 4919.7863) (3200.0916 4906.6718) (3191.771 4899.0382) (3188.7023 4898.0916)
      (3185.3435 4896.2901) (3182.4275 4893.9084) (3180.0458 4890.9924) (3178.2443 4887.6336) (3177.2977 4884.5649)
      (3169.6641 4876.2443) (3156.5496 4859.1603) (3144.9771 4840.9924) (3135.0382 4821.8931) (3126.7939 4801.9847)
      (3120.3206 4781.4504) (3115.6641 4760.4275) (3112.855 4739.0687) (3112.3511 4727.7863) (3110.8702 4724.9466)
      (3109.7557 4721.2977) (3109.3893 4717.5573) (3109.7557 4713.8168) (3110.8702 4710.1679) (3112.3511 4707.3282)
      (3112.855 4696.0458) (3115.6641 4674.687) (3120.3206 4653.6641) (3126.7939 4633.1298) (3135.0382 4613.2214)
      (3144.9771 4594.1221) (3156.5496 4575.9542) (3169.6641 4558.8702) (3177.2977 4550.5496) (3178.2443 4547.4809)
      (3180.0458 4544.1221) (3182.4275 4541.2061) (3185.3435 4538.8244) (3188.7023 4537.0229) (3191.771 4536.0763)
      (3200.0916 4528.4427) (3217.1756 4515.3282) (3235.3435 4503.7557) (3254.4427 4493.8168) (3274.3511 4485.5725)
      (3294.8855 4479.0992) (3315.9084 4474.4427) (3324.687 4473.2824)
    ))
    ; P2465 -- see feature_dimensions_mm.csv
    ("06_ORNAMENT" 1 (
      (3337.2366 5487.374) (3335.6183 5484.9313) (3332.2901 5478.0305) (3329.6031 5470.2748) (3327.6336 5461.8779)
      (3326.4275 5453.0382) (3326.0305 5443.9695) (3326.4275 5434.9008) (3327.6336 5426.0611) (3329.6031 5417.6641)
      (3332.2901 5409.9084) (3335.6183 5403.0076) (3339.5267 5397.0992) (3343.9084 5392.3511) (3348.6565 5388.8702)
      (3353.6489 5386.7481) (3358.7786 5386.0305) (3363.9084 5386.7481) (3368.9008 5388.8702) (3373.6489 5392.3511)
      (3378.0305 5397.0992) (3381.9389 5403.0076) (3385.2672 5409.9084) (3387.9542 5417.6641) (3389.9237 5426.0611)
      (3391.1298 5434.9008) (3391.5267 5443.9695) (3391.1298 5453.0382) (3389.9237 5461.8779) (3388.1679 5469.4046)
      (3372.1832 5475.3893)
    ))
    ; P2466 -- see feature_dimensions_mm.csv
    ("06_ORNAMENT" 0 (
      (3344.626 4412.2137) (3344.9618 4411.7252) (3345.4351 4410.0916) (3345.7557 4408.0) (3345.9847 4406.229)
    ))
    ; P2467 -- see feature_dimensions_mm.csv
    ("06_ORNAMENT" 0 (
      (3358.7786 4528.626) (3355.0382 4528.2595) (3351.3893 4527.145) (3347.9084 4525.3282) (3344.7176 4522.855)
      (3341.8626 4519.771) (3339.4198 4516.1679) (3337.4504 4512.1221) (3336.0153 4507.7405) (3335.145 4503.1298)
      (3334.855 4498.3969) (3335.145 4493.6641) (3336.0153 4489.0534) (3337.4504 4484.6718) (3339.4198 4480.626)
      (3341.8626 4477.0229) (3344.7176 4473.9389) (3345.5573 4473.2824)
    ))
    ; P2468 -- see feature_dimensions_mm.csv
    ("06_ORNAMENT" 0 (
      (3345.9847 5001.6489) (3346.0763 5000.9008) (3346.5191 4998.0611) (3347.2366 4995.0229) (3348.2901 4992.0)
      (3349.7405 4989.1603) (3350.0153 4988.7786) (3348.9618 4987.7252) (3347.4504 4982.0611) (3348.9618 4976.3969)
      (3353.1145 4972.2443) (3358.7786 4970.7176) (3364.4427 4972.2443) (3368.5954 4976.3969) (3370.1221 4982.0611)
      (3368.5954 4987.7252) (3367.542 4988.7786) (3367.8168 4989.1603) (3369.2672 4992.0) (3370.3206 4995.0229)
      (3371.0382 4998.0611) (3371.4809 5000.9008) (3371.5725 5001.6489)
    ))
    ; P2469 -- see feature_dimensions_mm.csv
    ("06_ORNAMENT" 0 (
      (3371.5725 5001.6489) (3358.7786 5002.2137) (3345.9847 5001.6489)
    ))
    ; P2470 -- see feature_dimensions_mm.csv
    ("06_ORNAMENT" 0 (
      (3345.9847 4406.229) (3346.0763 4405.4809) (3346.5191 4402.6412) (3347.2366 4399.6031) (3348.2901 4396.5802)
      (3349.7405 4393.7405) (3350.0153 4393.3588) (3348.9618 4392.3053) (3347.4504 4386.6412) (3348.9618 4380.9771)
      (3353.1145 4376.8244) (3358.7786 4375.2977) (3364.4427 4376.8244) (3368.5954 4380.9771) (3370.1221 4386.6412)
      (3368.5954 4392.3053) (3367.542 4393.3588) (3367.8168 4393.7405) (3369.2672 4396.5802) (3370.3206 4399.6031)
      (3371.0382 4402.6412) (3371.4809 4405.4809) (3371.5725 4406.229)
    ))
    ; P2471 -- see feature_dimensions_mm.csv
    ("06_ORNAMENT" 0 (
      (3371.5725 4406.229) (3358.7786 4406.7939) (3345.9847 4406.229)
    ))
    ; P2472 -- see feature_dimensions_mm.csv
    ("06_ORNAMENT" 0 (
      (3372.0 4473.2824) (3372.8397 4473.9389) (3375.6947 4477.0229) (3378.1374 4480.626) (3380.1069 4484.6718)
      (3381.542 4489.0534) (3382.4122 4493.6641) (3382.7176 4498.3969) (3382.4122 4503.1298) (3381.542 4507.7405)
      (3380.1069 4512.1221) (3378.1374 4516.1679) (3375.6947 4519.771) (3372.8397 4522.855) (3369.6489 4525.3282)
      (3366.1679 4527.145) (3362.5191 4528.2595) (3358.7786 4528.626)
    ))
    ; P2473 -- see feature_dimensions_mm.csv
    ("06_ORNAMENT" 1 (
      (3358.7786 4528.626) (3363.9084 4529.3435) (3368.9008 4531.4656) (3373.6489 4534.9466) (3378.0305 4539.6947)
      (3381.9389 4545.6031) (3385.2672 4552.5038) (3387.9542 4560.2595) (3389.9237 4568.6565) (3391.1298 4577.4962)
      (3391.5267 4586.5649) (3391.1298 4595.6336) (3389.9237 4604.4733) (3387.9542 4612.8702) (3385.2672 4620.626)
      (3381.9389 4627.5267) (3378.0305 4633.4351) (3373.6489 4638.1832) (3368.9008 4641.6641) (3363.9084 4643.7863)
      (3358.7786 4644.5038) (3353.6489 4643.7863) (3348.6565 4641.6641) (3343.9084 4638.1832) (3339.5267 4633.4351)
      (3335.6183 4627.5267) (3332.2901 4620.626) (3329.6031 4612.8702) (3327.6336 4604.4733) (3326.4275 4595.6336)
      (3326.0305 4586.5649) (3326.4275 4577.4962) (3327.6336 4568.6565) (3329.6031 4560.2595) (3332.2901 4552.5038)
      (3335.6183 4545.6031) (3339.5267 4539.6947) (3343.9084 4534.9466) (3348.6565 4531.4656) (3353.6489 4529.3435)
    ))
    ; P2474 -- see feature_dimensions_mm.csv
    ("06_ORNAMENT" 0 (
      (3642.3359 4742.4885) (3639.1145 4766.9924) (3633.7405 4791.2366) (3626.2748 4814.916) (3616.7634 4837.8626)
      (3605.2977 4859.8779) (3591.9542 4880.8244) (3576.8397 4900.5344) (3560.0611 4918.8397) (3541.7557 4935.6183)
      (3522.0458 4950.7328) (3501.1145 4964.0763) (3479.084 4975.542) (3456.1374 4985.0534) (3432.458 4992.5191)
      (3408.2137 4997.8931) (3383.5878 5001.1298) (3371.5725 5001.6489)
    ))
    ; P2475 -- see feature_dimensions_mm.csv
    ("06_ORNAMENT" 0 (
      (3371.5725 5001.6489) (3371.8015 5003.4198) (3372.1221 5005.5115) (3372.5954 5007.145) (3373.374 5008.3053)
      (3374.5344 5009.084) (3376.1679 5009.5573) (3378.2595 5009.8779) (3380.7786 5010.1985) (3383.6183 5010.6412)
      (3386.6565 5011.3588) (3389.6794 5012.4122) (3392.5191 5013.8626) (3394.9771 5015.6947) (3396.8702 5017.8931)
      (3398.0611 5020.3206) (3398.4733 5022.9008) (3398.0611 5025.4809) (3396.8702 5027.9084) (3394.9771 5030.1069)
      (3394.0611 5030.7786) (3408.2137 5032.6412) (3432.458 5038.0153) (3456.1374 5045.4809) (3479.084 5054.9924)
      (3501.1145 5066.458) (3522.0458 5079.8015) (3541.7557 5094.916) (3560.0611 5111.6947) (3576.8397 5130.0)
      (3591.9542 5149.7099) (3605.2977 5170.6412) (3616.7634 5192.6718) (3626.2748 5215.6183) (3633.7405 5239.2977)
      (3639.1145 5263.542) (3642.3511 5288.1679) (3643.4351 5312.9771) (3643.0687 5321.2519) (3634.916 5330.2901)
    ))
    ; P2476 -- see feature_dimensions_mm.csv
    ("06_ORNAMENT" 0 (
      (3642.8855 4134.5802) (3642.3511 4146.9466) (3639.1145 4171.5725) (3633.7405 4195.8168) (3626.2748 4219.4962)
      (3616.7634 4242.4427) (3605.2977 4264.458) (3591.9542 4285.4046) (3576.8397 4305.1145) (3560.0611 4323.4198)
      (3541.7557 4340.1985) (3522.0458 4355.313) (3501.1145 4368.6565) (3479.084 4380.1221) (3456.1374 4389.6336)
      (3432.458 4397.0992) (3408.2137 4402.4733) (3383.5878 4405.7099) (3371.5725 4406.229)
    ))
    ; P2477 -- see feature_dimensions_mm.csv
    ("06_ORNAMENT" 0 (
      (3371.5725 4406.229) (3371.8015 4408.0) (3372.1221 4410.0916) (3372.5954 4411.7252) (3372.9313 4412.2137)
    ))
    ; P2478 -- see feature_dimensions_mm.csv
    ("06_ORNAMENT" 0 (
      (3449.6336 5444.9618) (3449.2061 5445.145)
    ))
    ; P2479 -- see feature_dimensions_mm.csv
    ("06_ORNAMENT" 0 (
      (3497.6336 5422.5496) (3485.7863 5428.5344) (3449.6336 5444.9618)
    ))
    ; P2480 -- see feature_dimensions_mm.csv
    ("06_ORNAMENT" 0 (
      (3449.6336 5444.9618) (3449.374 5444.8397) (3442.0458 5440.2901) (3434.9466 5434.8855) (3428.2443 5428.7634)
      (3422.1221 5422.0611) (3416.7176 5414.9618) (3412.1679 5407.6336) (3408.5954 5400.2595) (3406.0611 5393.0076)
      (3404.6412 5386.0763) (3404.3817 5379.6183) (3405.2824 5373.8015) (3407.313 5368.7634) (3410.4427 5364.6412)
      (3414.5649 5361.5115) (3419.6031 5359.4809) (3425.4198 5358.5802) (3431.8779 5358.8397) (3438.8092 5360.2595)
      (3446.0611 5362.7939) (3453.4351 5366.3664) (3460.7634 5370.916) (3467.8626 5376.3206) (3474.5649 5382.4427)
      (3480.687 5389.145) (3486.0916 5396.2443) (3490.6412 5403.5725) (3494.2137 5410.9466) (3496.7481 5418.1985)
      (3497.6336 5422.5496)
    ))
    ; P2481 -- see feature_dimensions_mm.csv
    ("06_ORNAMENT" 0 (
      (3471.313 4473.2824) (3504.626 4473.2824)
    ))
    ; P2482 -- see feature_dimensions_mm.csv
    ("06_ORNAMENT" 1 (
      (3471.313 4473.2824) (3469.8168 4478.855) (3465.6641 4483.0076) (3460.0 4484.5191) (3454.3359 4483.0076)
      (3450.1832 4478.855) (3448.687 4473.2824)
    ))
    ; P2483 -- see feature_dimensions_mm.csv
    ("06_ORNAMENT" 0 (
      (3482.0305 4412.2137) (3482.3664 4411.7252) (3482.8397 4410.0916) (3483.1603 4408.0) (3483.4809 4405.4809)
      (3483.9237 4402.6412) (3484.6412 4399.6031) (3485.6947 4396.5802) (3487.145 4393.7405) (3488.9771 4391.2824)
      (3491.1756 4389.3893) (3493.6031 4388.1985) (3496.1832 4387.7863) (3498.7634 4388.1985) (3501.1908 4389.3893)
      (3503.3893 4391.2824) (3505.2214 4393.7405) (3506.6718 4396.5802) (3507.7252 4399.6031) (3508.4427 4402.6412)
      (3508.8855 4405.4809) (3509.2061 4408.0) (3509.5267 4410.0916) (3510.0 4411.7252) (3510.3359 4412.2137)
    ))
    ; P2484 -- see feature_dimensions_mm.csv
    ("06_ORNAMENT" 0 (
      (3531.7557 5404.5649) (3520.5954 5410.9313) (3497.6336 5422.5496)
    ))
    ; P2485 -- see feature_dimensions_mm.csv
    ("06_ORNAMENT" 0 (
      (3504.626 4473.2824) (3694.6565 4473.2824)
    ))
    ; P2486 -- see feature_dimensions_mm.csv
    ("06_ORNAMENT" 0 (
      (3504.626 4473.2824) (3522.0458 4484.3817) (3541.7557 4499.4962) (3560.0611 4516.2748) (3576.8397 4534.5802)
      (3591.9542 4554.2901) (3605.2977 4575.2214) (3616.7634 4597.2519) (3626.2748 4620.1985) (3633.7405 4643.8779)
      (3639.1145 4668.1221) (3642.3511 4692.7481) (3643.4351 4717.5573) (3642.5496 4737.8931)
    ))
    ; P2487 -- see feature_dimensions_mm.csv
    ("06_ORNAMENT" 0 (
      (3553.2672 5392.3053) (3531.7557 5404.5649)
    ))
    ; P2488 -- see feature_dimensions_mm.csv
    ("06_ORNAMENT" 0 (
      (3531.7557 5404.5649) (3530.3206 5401.7405) (3529.084 5393.9542) (3530.3206 5386.1679) (3533.8931 5379.145)
      (3539.4656 5373.5725) (3546.4885 5370.0) (3554.2748 5368.7634) (3562.0611 5370.0) (3569.084 5373.5725)
      (3574.1985 5378.687)
    ))
    ; P2489 -- see feature_dimensions_mm.csv
    ("06_ORNAMENT" 0 (
      (3642.5496 4737.8931) (3642.3511 4742.3664) (3642.3359 4742.4885)
    ))
    ; P2490 -- see feature_dimensions_mm.csv
    ("06_ORNAMENT" 0 (
      (3642.3359 4742.4885) (3641.9847 4740.7176) (3642.5496 4737.8931)
    ))
    ; P2491 -- see feature_dimensions_mm.csv
    ("06_ORNAMENT" 0 (
      (3642.5496 4737.8931) (3643.2061 4734.5802) (3646.687 4729.374) (3651.8779 4725.9084) (3658.0153 4724.687)
      (3664.1527 4725.9084) (3669.3435 4729.374) (3672.8244 4734.5802) (3674.0458 4740.7176) (3672.8244 4746.855)
      (3669.3435 4752.0458) (3664.1527 4755.5267) (3658.0153 4756.7481) (3651.8779 4755.5267) (3646.687 4752.0458)
      (3643.2061 4746.855) (3642.3359 4742.4885)
    ))
    ; P2492 -- see feature_dimensions_mm.csv
    ("06_ORNAMENT" 0 (
      (3643.374 4123.6489) (3642.8855 4134.5802)
    ))
    ; P2493 -- see feature_dimensions_mm.csv
    ("06_ORNAMENT" 0 (
      (3642.8855 4134.5802) (3641.9847 4130.0305) (3643.2061 4123.8931) (3643.374 4123.6489)
    ))
    ; P2494 -- see feature_dimensions_mm.csv
    ("06_ORNAMENT" 0 (
      (3643.374 4123.6489) (3646.687 4118.687) (3651.8779 4115.2214) (3658.0153 4114.0) (3664.1527 4115.2214)
      (3669.3435 4118.687) (3672.8244 4123.8931) (3674.0458 4130.0305) (3672.8244 4136.1679) (3669.3435 4141.3588)
      (3664.1527 4144.8397) (3658.0153 4146.0611) (3651.8779 4144.8397) (3646.687 4141.3588) (3643.2061 4136.1679)
      (3642.8855 4134.5802)
    ))
    ; P2495 -- see feature_dimensions_mm.csv
    ("06_ORNAMENT" 0 (
      (3923.6641 4412.2137) (3908.3969 4412.2137) (3801.5267 4412.2137)
    ))
    ; P2496 -- see feature_dimensions_mm.csv
    ("06_ORNAMENT" 0 (
      (3801.5267 3832.0611) (3908.3969 3832.0611) (3923.6641 3832.0611)
    ))
    ; P2497 -- see feature_dimensions_mm.csv
    ("06_ORNAMENT" 0 (
      (3984.7328 4473.2824) (3984.7328 3679.3893)
    ))
    ; P2498 -- see feature_dimensions_mm.csv
    ("06_ORNAMENT" 0 (
      (4595.4198 3633.5878) (4595.4198 3664.1221) (4595.4198 3679.3893) (4595.4198 3740.458) (4595.4198 5007.6336)
    ))
    ; P2499 -- see feature_dimensions_mm.csv
    ("06_ORNAMENT" 1 (
      (4595.4198 5007.6336) (4560.9008 5004.6718) (4523.2061 4999.6031) (4482.9313 4992.5191) (4440.687 4983.5267)
      (4397.0992 4972.687) (4352.7786 4960.1221) (4308.3053 4945.8931) (4288.1679 4938.6718) (4293.0534 4941.7863)
      (4335.4962 4970.916) (4376.5191 5001.0687) (4415.6489 5031.7405) (4452.3511 5062.4275) (4486.1374 5092.6565)
      (4516.5038 5121.9237) (4542.916 5149.7252) (4564.8855 5175.5725) (4529.7252 5162.4733) (4491.7252 5146.3817)
      (4451.4962 5127.5267) (4409.6794 5106.2137) (4366.855 5082.7023) (4323.6336 5057.2519) (4313.2214 5050.6718)
      (4314.0153 5051.4809) (4338.3511 5077.4504) (4352.6565 5079.4656) (4362.5954 5082.1374) (4363.0687 5085.4046)
      (4356.0763 5090.0305) (4351.9084 5091.9389) (4387.313 5132.0) (4420.4427 5171.7557) (4450.6412 5210.3511)
      (4477.4351 5247.1756) (4500.3969 5281.5878) (4519.084 5312.9771) (4484.8397 5291.4504) (4448.1527 5266.1985)
      (4411.084 5238.7634) (4414.5496 5249.1145) (4417.0229 5259.9695) (4418.1527 5270.7939) (4417.6641 5281.2672)
      (4415.2672 5290.9924) (4410.6107 5300.5496) (4403.8168 5310.5038) (4395.2977 5320.5344) (4394.7481 5321.0992)
      (4405.7405 5333.542) (4421.7557 5354.855) (4423.9847 5358.3053) (4433.4504 5359.2977) (4446.916 5361.7405)
      (4454.1985 5364.2748) (4454.5496 5367.374) (4449.4198 5371.7405) (4440.2901 5377.1908) (4437.2061 5378.855)
      (4450.0763 5401.6336) (4462.2595 5426.3206) (4473.0076 5451.3588) (4482.2748 5476.3817) (4489.9847 5501.0076)
      (4496.0611 5524.8397) (4500.4427 5547.4962) (4503.0534 5568.6107) (4503.8168 5587.7863) (4488.0458 5573.8931)
      (4488.0153 5573.8473) (4484.4275 5580.626) (4478.1832 5590.1374) (4470.9924 5599.4046) (4463.1756 5608.1527)
      (4455.0382 5616.0458) (4446.9008 5622.7939) (4439.084 5628.0916) (4431.1756 5632.3817) (4422.687 5636.1679)
      (4413.8473 5639.1756) (4404.8702 5641.145) (4395.9695 5641.8321) (4387.3588 5640.9771) (4379.2672 5638.3053)
      (4371.9084 5633.5878) (4365.0229 5626.626) (4358.3206 5617.6183) (4351.8931 5606.7939) (4345.8779 5594.4275)
      (4340.3817 5580.7786) (4335.542 5566.0916) (4331.4504 5550.626) (4328.2443 5534.6565) (4325.2977 5516.6107)
      (4322.229 5495.5878) (4319.5115 5472.7939) (4317.6489 5449.4656) (4317.0992 5426.8244) (4318.3664 5406.0916)
      (4321.9237 5388.5038) (4328.2443 5375.2672) (4339.2977 5366.3817) (4355.4351 5360.6718) (4359.4504 5360.0305)
      (4357.5573 5353.3588) (4357.2977 5352.0305) (4352.6412 5355.0229) (4341.9847 5360.6107) (4331.1908 5365.145)
      (4319.6183 5369.1298) (4307.5725 5372.3053) (4295.3282 5374.3817) (4283.1908 5375.1145) (4271.4504 5374.2137)
      (4260.4275 5371.4046) (4250.3817 5366.4122) (4240.9924 5359.0687) (4231.8473 5349.5573) (4223.084 5338.1221)
      (4214.8855 5325.0687) (4207.4046 5310.6565) (4200.7939 5295.1603) (4195.2214 5278.8397) (4190.8397 5261.9847)
      (4186.8092 5242.9313) (4182.626 5220.7328) (4178.9313 5196.687) (4176.3817 5172.0611) (4175.6489 5148.1679)
      (4177.374 5126.2901) (4182.2137 5107.7099) (4190.8397 5093.7405) (4205.9084 5084.3511) (4227.8931 5078.3359)
      (4209.3588 5059.9237) (4171.9542 5020.2748) (4136.7939 4980.2443) (4104.4885 4940.229) (4075.6183 4900.6412)
      (4050.7786 4861.9084) (4030.5344 4824.4275) (4054.3206 4837.8321) (4037.4046 4816.0305) (4065.1908 4824.7786)
      (4044.2748 4807.6336) (4071.8626 4808.4733) (4051.145 4799.2366) (4075.0992 4791.7863) (4058.0153 4790.8397)
      (4071.2519 4780.1527) (4064.8855 4782.4427) (4071.8779 4768.8702) (4072.4885 4742.3817) (4076.4275 4709.2824)
      (4083.2824 4675.1756) (4092.7328 4640.4733) (4104.4427 4605.5878) (4118.1069 4570.916) (4133.4046 4536.8855)
      (4150.0153 4503.9084) (4167.6336 4472.3817) (4185.9237 4442.7328) (4199.8779 4422.2748) (4195.2214 4408.6107)
      (4190.8397 4391.7557) (4186.8092 4372.7023) (4182.626 4350.5038) (4178.9313 4326.458) (4176.3817 4301.8321)
      (4175.6489 4277.9389) (4177.1145 4259.2214) (4173.1908 4259.8779) (4161.0534 4260.6107) (4149.313 4259.7099)
      (4138.2901 4256.9008) (4128.2443 4251.9084) (4118.855 4244.5649) (4109.7099 4235.0534) (4100.9466 4223.6183)
      (4092.7481 4210.5649) (4085.2672 4196.1527) (4078.6565 4180.6565) (4073.084 4164.3359) (4068.7023 4147.4809)
      (4064.6718 4128.4275) (4060.4885 4106.229) (4056.7939 4082.1832) (4054.2443 4057.5573) (4053.5115 4033.6641)
      (4055.2366 4011.7863) (4060.0763 3993.2061) (4068.7023 3979.2366) (4083.771 3969.8473) (4105.7863 3963.8321)
      (4128.0305 3961.1145) (4123.2977 3960.7634) (4113.7405 3958.3969) (4105.0382 3954.1985) (4096.9008 3948.0153)
      (4088.9771 3940.0) (4081.3893 3930.3817) (4074.2748 3919.3893) (4067.7863 3907.2519) (4062.0611 3894.1985)
      (4057.2214 3880.458) (4053.4351 3866.2595) (4049.9542 3850.2137) (4046.3206 3831.5267) (4043.1145 3811.2672)
      (4040.9008 3790.5344) (4040.2595 3770.4122) (4041.7557 3751.9847) (4045.9542 3736.3511) (4053.4351 3724.5802)
      (4066.4885 3716.6718) (4085.5725 3711.6031) (4108.4733 3708.8855) (4132.9466 3708.0916) (4156.7939 3708.7328)
      (4177.771 3710.3817) (4193.6794 3712.5496) (4202.2901 3714.8092) (4202.7023 3717.5725) (4196.6412 3721.4504)
      (4185.8473 3726.2901) (4172.0305 3731.9084) (4156.9008 3738.1374) (4142.1832 3744.8092) (4129.6183 3751.7405)
      (4120.916 3758.7786) (4115.3282 3766.2595) (4110.916 3774.5038) (4107.5573 3783.2824) (4105.1603 3792.3664)
      (4103.6183 3801.5267) (4102.8244 3810.5344) (4102.6718 3819.1603) (4103.0534 3827.1756) (4104.2137 3834.9771)
      (4106.3664 3842.9618) (4109.3435 3850.8702) (4112.9771 3858.4733) (4117.0992 3865.5267) (4121.5725 3871.771)
      (4126.1985 3876.9924) (4130.8397 3880.916) (4136.1985 3883.4962) (4142.7176 3884.9466) (4149.8779 3885.4046)
      (4157.145 3885.0382) (4163.9695 3884.0) (4169.8168 3882.458) (4174.1679 3880.5649) (4176.4885 3878.4733)
      (4176.1374 3875.9847) (4173.3588 3872.8855) (4168.916 3869.2519) (4163.5878 3865.1908) (4158.1374 3860.8092)
      (4153.3282 3856.1985) (4149.9237 3851.4656) (4148.7023 3846.7176) (4149.5115 3841.3588) (4151.542 3835.0382)
      (4154.6107 3828.229) (4158.5038 3821.374) (4163.0382 3814.9466) (4168.0 3809.3893) (4170.2443 3807.5725)
      (4167.9389 3801.5267) (4173.771 3804.916) (4178.4733 3802.7481) (4184.2901 3802.0458) (4191.084 3802.5802)
      (4198.4885 3804.229) (4206.1374 3806.8702) (4213.6794 3810.3664) (4220.7634 3814.5954) (4227.0076 3819.4351)
      (4232.0611 3824.7328) (4236.3969 3830.916) (4240.5496 3838.3053) (4244.2595 3846.5649) (4247.313 3855.4198)
      (4249.4504 3864.5649) (4249.5115 3865.0687) (4255.2824 3870.7634) (4271.8931 3888.6412) (4287.8168 3907.1603)
      (4302.916 3926.0458) (4316.9924 3945.0076) (4329.9084 3963.7405) (4332.6107 3968.0) (4356.5344 3968.4275)
      (4383.9695 3969.8626) (4404.7786 3971.771) (4416.0305 3973.7405) (4416.5649 3976.1527) (4408.6565 3979.5573)
      (4394.5344 3983.7863) (4376.458 3988.7023) (4356.6718 3994.1527) (4349.7252 3996.2595) (4351.5115 3999.3435)
      (4359.8779 4015.6336) (4366.4122 4030.5344) (4351.4351 4020.626) (4335.5725 4008.9466) (4328.5191 4003.2824)
      (4321.5725 4005.8473) (4331.0076 4018.4427) (4348.6107 4043.2672) (4362.2443 4063.6947) (4364.7023 4061.3588)
      (4371.2061 4056.5038) (4378.0153 4052.8092) (4384.8855 4050.687) (4392.4885 4050.0611) (4401.374 4050.5344)
      (4411.0534 4051.9847) (4421.0534 4054.2901) (4430.9313 4057.3588) (4440.1832 4061.0534) (4448.3511 4065.2824)
      (4454.9618 4069.9237) (4460.626 4075.3435) (4466.0458 4081.8015) (4470.916 4089.0229) (4474.916 4096.7786)
      (4477.7099 4104.7786) (4478.9924 4112.7481) (4478.4275 4120.458) (4475.7252 4127.6336) (4470.458 4134.6718)
      (4462.7481 4142.0153) (4453.0992 4149.4046) (4441.9847 4156.626) (4429.8931 4163.4198) (4421.7252 4167.4198)
      (4425.6794 4167.0382) (4452.0458 4166.3359) (4477.7252 4166.9008) (4500.3206 4168.3359) (4517.4504 4170.2443)
      (4526.7176 4172.2137) (4527.1603 4174.626) (4520.6412 4178.0305) (4509.0076 4182.2595) (4494.1221 4187.1756)
      (4477.8321 4192.626) (4462.0 4198.458) (4448.458 4204.5344) (4439.084 4210.687) (4433.0687 4217.2366)
      (4430.1374 4221.6794) (4433.4198 4227.2824) (4446.9924 4252.3359) (4458.0153 4274.8092) (4437.6183 4255.9389)
      (4422.0153 4240.5496) (4420.458 4248.0916) (4419.9695 4252.6107) (4434.3969 4274.9618) (4455.4656 4309.084)
      (4462.4885 4321.0687) (4462.5649 4321.084) (4470.2748 4321.4809) (4478.0916 4321.1603) (4485.4504 4320.2595)
      (4491.7557 4318.916) (4496.4427 4317.2519) (4498.9313 4315.4198) (4498.5496 4313.2519) (4495.5573 4310.5344)
      (4490.7786 4307.3435) (4485.0382 4303.8015) (4479.1603 4299.9695) (4473.9847 4295.9389) (4470.3206 4291.7863)
      (4469.0076 4287.6336) (4469.8779 4282.9466) (4472.0611 4277.4198) (4475.3588 4271.4504) (4479.5573 4265.4504)
      (4484.4427 4259.8321) (4489.8015 4254.9771) (4495.4046 4251.2824) (4501.0687 4249.1603) (4507.3282 4248.5344)
      (4514.6412 4249.0076) (4522.6107 4250.458) (4530.855 4252.7634) (4538.9924 4255.8321) (4546.6107 4259.5267)
      (4553.3282 4263.7557) (4558.7786 4268.3969) (4563.4504 4273.8168) (4567.9084 4280.2748) (4571.9237 4287.4962)
      (4575.2061 4295.2519) (4577.5115 4303.2519) (4578.5649 4311.2214) (4578.1069 4318.9313) (4575.8779 4326.1069)
      (4571.542 4333.145) (4565.1908 4340.4885) (4557.2366 4347.8779) (4548.0916 4355.0992) (4538.1374 4361.8931)
      (4527.7863 4368.0305) (4517.4351 4373.2824) (4507.4809 4377.4046) (4497.4046 4380.7481) (4495.8321 4381.1756)
      (4503.8168 4396.9466) (4489.8168 4382.8092) (4486.6107 4383.6794) (4475.3588 4386.0153) (4463.9389 4387.5573)
      (4452.6107 4388.0916) (4441.6489 4387.4198) (4431.3588 4385.3588) (4421.9847 4381.6794) (4413.7863 4376.626)
      (4414.5496 4378.8855) (4417.0229 4389.7405) (4418.1527 4400.5649) (4417.6641 4411.0382) (4415.2672 4420.7634)
      (4410.6107 4430.3206) (4403.8168 4440.2748) (4395.2977 4450.3053) (4385.4962 4460.1069) (4374.8397 4469.3282)
      (4363.7405 4477.6641) (4352.6412 4484.7939) (4341.9847 4490.3817) (4331.1908 4494.916) (4319.6183 4498.9008)
      (4307.5725 4502.0763) (4295.3282 4504.1527) (4283.1908 4504.8855) (4271.4504 4503.9847) (4260.4275 4501.1756)
      (4250.3817 4496.1832) (4240.9924 4488.8397) (4235.2824 4482.9008) (4227.8168 4508.3206) (4216.1221 4542.8244)
      (4202.8244 4577.2061) (4188.0153 4610.9924) (4180.2137 4626.6718) (4205.0534 4602.5344) (4235.6336 4575.2824)
      (4266.9618 4549.542) (4298.5344 4525.6031) (4329.8626 4503.7405) (4360.4427 4484.2443) (4389.771 4467.4046)
      (4417.374 4453.4809) (4442.7481 4442.7481) (4427.1908 4468.8244) (4408.6412 4496.3664) (4387.4351 4524.9771)
      (4363.8473 4554.1679) (4338.1832 4583.542) (4310.7786 4612.626) (4281.9084 4640.9924) (4251.8931 4668.2137)
      (4221.0534 4693.8168) (4214.8855 4698.4427) (4223.4504 4694.7481) (4262.4885 4679.9847) (4302.1832 4666.855)
      (4341.9542 4655.4198) (4381.2061 4645.7405) (4419.3588 4637.8779) (4455.8626 4631.9084) (4490.1221 4627.8931)
      (4521.5725 4625.8779) (4549.6183 4625.9542) (4524.4122 4643.8779) (4495.8321 4662.0153) (4464.3206 4680.0458)
      (4430.3511 4697.7252) (4394.3817 4714.7176) (4356.9008 4730.7786) (4318.3511 4745.6183) (4279.2061 4758.916)
      (4241.4351 4769.9847) (4244.1679 4769.8931) (4286.8092 4770.3359) (4329.4504 4772.5344) (4371.5267 4776.3511)
      (4412.4885 4781.6031) (4451.7252 4788.1679) (4488.687 4795.8779) (4522.7939 4804.5954) (4553.4656 4814.1679)
      (4580.1527 4824.4275) (4549.5267 4831.9695) (4515.6183 4838.458) (4478.9466 4843.8015) (4440.0611 4847.9084)
      (4399.542 4850.6718) (4357.9084 4852.0) (4315.7405 4851.7863) (4276.0458 4850.0611) (4301.4809 4858.3359)
      (4345.8626 4874.626) (4389.1756 4892.2595) (4430.8855 4910.9008) (4470.3969 4930.229) (4507.1756 4949.9084)
      (4540.6412 4969.5878) (4570.2443 4988.9313)
    ))
    ; P2500 -- see feature_dimensions_mm.csv
    ("06_ORNAMENT" 0 (
      (8996.4733 3832.0611) (8998.0153 3834.3817) (8999.2366 3840.5038) (8998.0153 3846.6412) (8994.5344 3851.8473)
      (8989.3435 3855.313) (8983.2061 3856.5344) (8977.0687 3855.313) (8971.8779 3851.8473) (8968.3969 3846.6412)
      (8967.1756 3840.5038) (8968.3969 3834.3817) (8969.9389 3832.0611)
    ))
    ; P2501 -- see feature_dimensions_mm.csv
    ("06_ORNAMENT" 0 (
      (8970.4733 5281.6489) (8971.5115 5280.0916) (8971.6183 5277.8626) (8974.2137 5258.1679) (8978.5038 5238.7634)
      (8981.2061 5230.1832) (8977.0687 5229.3588) (8971.8779 5225.8931) (8968.3969 5220.687) (8967.1756 5214.5496)
      (8968.3969 5208.4275) (8971.8779 5203.2214) (8977.0687 5199.7405) (8983.2061 5198.5191) (8989.3435 5199.7405)
      (8992.0458 5201.5573) (8992.0916 5201.4656) (9001.2519 5183.8473) (9011.9389 5167.0992) (9024.0305 5151.3282)
      (9037.4504 5136.687) (9052.0916 5123.2672) (9067.8626 5111.1756) (9084.6107 5100.4885) (9102.229 5091.3282)
      (9120.5802 5083.7252) (9139.5267 5077.7405) (9158.9313 5073.4504) (9178.626 5070.855) (9198.4733 5069.9847)
      (9218.3206 5070.855) (9238.0153 5073.4504) (9257.4198 5077.7405) (9276.3664 5083.7252) (9294.7176 5091.3282)
      (9312.3359 5100.4885) (9329.084 5111.1756) (9344.855 5123.2672) (9359.4962 5136.687) (9372.916 5151.3282)
      (9385.0076 5167.0992) (9395.6947 5183.8473) (9404.855 5201.4656) (9404.9008 5201.5573) (9407.6031 5199.7405)
      (9413.7405 5198.5191) (9419.8779 5199.7405) (9425.0687 5203.2214) (9428.5496 5208.4275) (9429.771 5214.5496)
      (9428.5496 5220.687) (9425.0687 5225.8931) (9419.8779 5229.3588) (9415.7405 5230.1832) (9418.4427 5238.7634)
      (9422.7328 5258.1679) (9425.3282 5277.8626) (9425.4351 5280.0916) (9428.5496 5284.7634) (9429.771 5290.8855)
      (9428.5496 5297.0229) (9426.0611 5300.7481) (9425.3282 5317.5573) (9422.7328 5337.2519) (9419.4046 5352.3206)
      (9419.8779 5352.4122) (9425.0687 5355.8931) (9428.5496 5361.0992) (9429.771 5367.2214) (9428.5496 5373.3588)
      (9425.0687 5378.5649) (9419.8779 5382.0305) (9413.7405 5383.2519) (9409.6336 5382.4427) (9404.855 5393.9542)
      (9395.6947 5411.5725) (9385.0076 5428.3206) (9372.916 5444.0916) (9359.4962 5458.7328) (9344.855 5472.1527)
      (9336.7786 5478.3511)
    ))
    ; P2502 -- see feature_dimensions_mm.csv
    ("06_ORNAMENT" 0 (
      (8991.6947 5309.5878) (8988.626 5305.8473)
    ))
    ; P2503 -- see feature_dimensions_mm.csv
    ("06_ORNAMENT" 0 (
      (8998.0458 3999.1756) (8998.0153 3999.313) (8997.8168 3999.6031)
    ))
    ; P2504 -- see feature_dimensions_mm.csv
    ("06_ORNAMENT" 0 (
      (8997.8168 3999.6031) (8998.0458 3999.1756)
    ))
    ; P2505 -- see feature_dimensions_mm.csv
    ("06_ORNAMENT" 0 (
      (8997.8168 3999.6031) (8994.5344 4004.5191) (8989.3435 4007.9847) (8983.2061 4009.2061) (8977.0687 4007.9847)
      (8971.8779 4004.5191) (8968.3969 3999.313) (8967.1756 3993.1756) (8968.3969 3987.0534) (8971.8779 3981.8473)
      (8977.0687 3978.3664) (8983.2061 3977.145) (8989.3435 3978.3664) (8994.5344 3981.8473) (8998.0153 3987.0534)
      (8999.2366 3993.1756) (8998.0458 3999.1756)
    ))
    ; P2506 -- see feature_dimensions_mm.csv
    ("06_ORNAMENT" 0 (
      (9399.1298 3999.6031) (9404.855 4010.626) (9412.458 4028.9771) (9418.4427 4047.9237) (9419.9542 4054.7634)
      (9425.0687 4058.1832) (9428.5496 4063.3893) (9429.771 4069.5115) (9428.5496 4075.6489) (9425.0687 4080.855)
      (9424.5649 4081.1908) (9425.3282 4087.0229) (9426.1985 4106.8702) (9425.3282 4126.7176) (9424.3664 4134.0458)
      (9425.0687 4134.5191) (9428.5496 4139.7252) (9429.771 4145.8473) (9428.5496 4151.9847) (9425.0687 4157.1908)
      (9419.8779 4160.6565) (9419.5725 4160.7176) (9418.4427 4165.8168) (9412.458 4184.7634) (9404.855 4203.1145)
      (9395.6947 4220.7328) (9385.0076 4237.4809) (9372.916 4253.2519) (9359.4962 4267.8931) (9344.855 4281.313)
      (9329.084 4293.4046) (9312.3359 4304.0916) (9294.7176 4313.2519) (9276.3664 4320.855) (9257.4198 4326.8397)
      (9238.0153 4331.1298) (9218.3206 4333.7252) (9198.4733 4334.5954) (9178.626 4333.7252) (9158.9313 4331.1298)
      (9139.5267 4326.8397) (9120.5802 4320.855) (9102.229 4313.2519) (9084.6107 4304.0916) (9067.8626 4293.4046)
      (9052.0916 4281.313) (9037.4504 4267.8931) (9024.0305 4253.2519) (9011.9389 4237.4809) (9001.2519 4220.7328)
      (8992.0916 4203.1145) (8984.4885 4184.7634) (8978.5038 4165.8168) (8977.374 4160.7176) (8977.0687 4160.6565)
      (8971.8779 4157.1908) (8968.3969 4151.9847) (8967.1756 4145.8473) (8968.3969 4139.7252) (8971.8779 4134.5191)
      (8972.5802 4134.0458) (8971.6183 4126.7176) (8970.7481 4106.8702) (8971.6183 4087.0229) (8972.3817 4081.1908)
      (8971.8779 4080.855) (8968.3969 4075.6489) (8967.1756 4069.5115) (8968.3969 4063.3893) (8971.8779 4058.1832)
      (8976.9924 4054.7634) (8978.5038 4047.9237) (8984.4885 4028.9771) (8992.0916 4010.626) (8997.8168 3999.6031)
    ))
    ; P2507 -- see feature_dimensions_mm.csv
    ("06_ORNAMENT" 0 (
      (8998.0458 3999.1756) (9001.2519 3993.0076) (9011.9389 3976.2595) (9024.0305 3960.4885) (9037.4504 3945.8473)
      (9052.0916 3932.4275) (9067.8626 3920.3359) (9084.6107 3909.6489) (9102.229 3900.4885) (9120.5802 3892.8855)
      (9139.5267 3886.9008) (9158.9313 3882.6107) (9178.626 3880.0153) (9198.4733 3879.145) (9218.3206 3880.0153)
      (9238.0153 3882.6107) (9257.4198 3886.9008) (9276.3664 3892.8855) (9294.7176 3900.4885) (9312.3359 3909.6489)
      (9329.084 3920.3359) (9344.855 3932.4275) (9359.4962 3945.8473) (9372.916 3960.4885) (9385.0076 3976.2595)
      (9395.6947 3993.0076) (9398.9008 3999.1756)
    ))
    ; P2508 -- see feature_dimensions_mm.csv
    ("06_ORNAMENT" 0 (
      (9002.4275 5320.2443) (9001.7252 5314.916) (9001.3282 5305.8931) (9000.1527 5303.6336) (8999.2672 5300.7023)
      (8998.9618 5297.7099) (8999.2672 5294.7176) (9000.1527 5291.7863) (9001.3282 5289.5267) (9001.7252 5280.5038)
      (9003.9847 5263.4198) (9007.7099 5246.5954) (9012.8855 5230.1679) (9019.4809 5214.2443) (9027.4351 5198.9618)
      (9036.687 5184.4275) (9047.1756 5170.7634) (9053.2824 5164.1069) (9054.0458 5161.6489) (9055.4962 5158.9618)
      (9057.4046 5156.6412) (9059.7252 5154.7328) (9062.4122 5153.2824) (9064.8702 5152.5191) (9071.5267 5146.4122)
      (9085.1908 5135.9237) (9099.7252 5126.6718) (9115.0076 5118.7176) (9130.9313 5112.1221) (9147.3588 5106.9466)
      (9164.1832 5103.2214) (9181.2672 5100.9618) (9190.2901 5100.5649) (9192.5496 5099.3893) (9195.4809 5098.4885)
      (9198.4733 5098.1985) (9201.4656 5098.4885) (9204.3969 5099.3893) (9206.6565 5100.5649) (9215.6794 5100.9618)
      (9232.7634 5103.2214) (9249.5878 5106.9466) (9266.0153 5112.1221) (9281.9389 5118.7176) (9297.2214 5126.6718)
      (9311.7557 5135.9237) (9325.4198 5146.4122) (9332.0763 5152.5191) (9334.5344 5153.2824) (9337.2214 5154.7328)
      (9339.542 5156.6412) (9341.4504 5158.9618) (9342.9008 5161.6489) (9343.6641 5164.1069) (9349.771 5170.7634)
      (9360.2595 5184.4275) (9369.5115 5198.9618) (9377.4656 5214.2443) (9384.0611 5230.1679) (9389.2366 5246.5954)
      (9392.9618 5263.4198) (9395.2214 5280.5038) (9395.6183 5289.5267) (9396.7939 5291.7863) (9397.6947 5294.7176)
      (9397.9847 5297.7099) (9397.6947 5300.7023) (9396.7939 5303.6336) (9395.6183 5305.8931) (9395.2214 5314.916)
      (9392.9618 5332.0) (9389.2366 5348.8244) (9384.0611 5365.2519) (9377.4656 5381.1756) (9369.5115 5396.458)
      (9360.2595 5410.9924) (9349.771 5424.6565) (9343.6641 5431.313) (9342.9008 5433.771) (9341.4504 5436.458)
      (9339.542 5438.7786) (9337.2214 5440.687) (9334.5344 5442.1374) (9332.0763 5442.9008) (9325.4198 5449.0076)
      (9311.7557 5459.4962) (9298.9771 5467.6336) (9310.5038 5471.0687)
    ))
    ; P2509 -- see feature_dimensions_mm.csv
    ("06_ORNAMENT" 0 (
      (9021.374 4412.2137) (9021.7863 4409.6336) (9022.9771 4407.2061) (9024.8702 4405.0076) (9027.3282 4403.1756)
      (9030.1679 4401.7252) (9033.1908 4400.6718) (9036.229 4399.9542) (9039.0687 4399.5115) (9041.5878 4399.1908)
      (9043.6794 4398.8702) (9045.313 4398.3969) (9046.4733 4397.6183) (9047.2519 4396.458) (9047.7252 4394.8244)
      (9048.0458 4392.7328) (9048.3664 4390.2137) (9048.8092 4387.374) (9049.5267 4384.3359) (9050.5802 4381.313)
      (9052.0305 4378.4733) (9053.8626 4376.0153) (9056.0611 4374.1221) (9058.4885 4372.9313) (9061.0687 4372.5191)
      (9063.6489 4372.9313) (9066.0763 4374.1221) (9068.2748 4376.0153) (9070.1069 4378.4733) (9071.5573 4381.313)
      (9072.6107 4384.3359) (9073.3282 4387.374) (9073.771 4390.2137) (9074.0916 4392.7328) (9074.4122 4394.8244)
      (9074.8855 4396.458) (9075.6641 4397.6183) (9076.8244 4398.3969) (9078.458 4398.8702) (9080.5496 4399.1908)
      (9083.0687 4399.5115) (9085.9084 4399.9542) (9088.9466 4400.6718) (9091.9695 4401.7252) (9094.8092 4403.1756)
      (9097.2672 4405.0076) (9099.1603 4407.2061) (9100.3511 4409.6336) (9100.7634 4412.2137)
    ))
    ; P2510 -- see feature_dimensions_mm.csv
    ("06_ORNAMENT" 0 (
      (9053.3588 5361.2672) (9031.4656 5345.5573) (9035.8473 5343.3282) (9042.0763 5342.3359) (9048.3053 5343.3282)
      (9053.9237 5346.1832) (9058.3817 5350.6412) (9061.2366 5356.2595) (9062.229 5362.4885) (9061.6031 5366.458)
    ))
    ; P2511 -- see feature_dimensions_mm.csv
    ("06_ORNAMENT" 0 (
      (9104.3359 5391.4656) (9088.0 5382.3511) (9088.0916 5381.8931) (9090.1221 5376.0916) (9092.9924 5370.1832)
      (9096.626 5364.3206) (9100.9466 5358.6412) (9105.8473 5353.2824) (9111.2061 5348.3817) (9116.8855 5344.0611)
      (9122.7481 5340.4275) (9128.6565 5337.5573) (9134.4427 5335.542) (9140.0 5334.4122) (9145.1603 5334.1985)
      (9149.8168 5334.916) (9153.8473 5336.5344) (9157.145 5339.0382) (9159.6489 5342.3359) (9161.2672 5346.3664)
      (9161.9847 5351.0229) (9161.771 5356.1832) (9160.6412 5361.7405) (9158.626 5367.5267) (9155.7557 5373.4351)
      (9152.1221 5379.2977) (9147.8015 5384.9771) (9142.9008 5390.3359) (9137.542 5395.2366) (9131.8626 5399.5573)
      (9126.7786 5402.7176)
    ))
    ; P2512 -- see feature_dimensions_mm.csv
    ("06_ORNAMENT" 0 (
      (9158.7786 4412.2137) (9159.1908 4409.6336) (9160.3817 4407.2061) (9162.2748 4405.0076) (9164.7328 4403.1756)
      (9167.5725 4401.7252) (9170.5954 4400.6718) (9173.6336 4399.9542) (9176.4733 4399.5115) (9178.9924 4399.1908)
      (9181.084 4398.8702) (9182.7176 4398.3969) (9183.8779 4397.6183) (9184.6565 4396.458) (9185.1298 4394.8244)
      (9185.4504 4392.7328) (9185.771 4390.2137) (9186.2137 4387.374) (9186.9313 4384.3359) (9187.9847 4381.313)
      (9189.4351 4378.4733) (9191.2672 4376.0153) (9193.4656 4374.1221) (9195.8931 4372.9313) (9198.4733 4372.5191)
      (9201.0534 4372.9313) (9203.4809 4374.1221) (9205.6794 4376.0153) (9207.5115 4378.4733) (9208.9618 4381.313)
      (9210.0153 4384.3359) (9210.7328 4387.374) (9211.1756 4390.2137) (9211.4962 4392.7328) (9211.8168 4394.8244)
      (9212.2901 4396.458) (9213.0687 4397.6183) (9214.229 4398.3969) (9215.8626 4398.8702) (9217.9542 4399.1908)
      (9220.4733 4399.5115) (9223.313 4399.9542) (9226.3511 4400.6718) (9229.374 4401.7252) (9232.2137 4403.1756)
      (9234.6718 4405.0076) (9236.5649 4407.2061) (9237.7557 4409.6336) (9238.1679 4412.2137)
    ))
    ; P2513 -- see feature_dimensions_mm.csv
    ("06_ORNAMENT" 0 (
      (9175.4351 5424.4275) (9175.1298 5423.542) (9173.5573 5416.8244) (9172.5954 5409.7557) (9172.2748 5402.5038)
      (9172.5954 5395.2519) (9173.5573 5388.1832) (9175.1298 5381.4656) (9177.2824 5375.2519) (9179.9542 5369.7252)
      (9183.0687 5365.0076) (9186.5802 5361.2061) (9190.3817 5358.4275) (9194.3817 5356.7176) (9198.4733 5356.1527)
      (9202.5649 5356.7176) (9206.5649 5358.4275) (9210.3664 5361.2061) (9213.8779 5365.0076) (9216.9924 5369.7252)
      (9219.6641 5375.2519) (9221.8168 5381.4656) (9223.3893 5388.1832) (9224.3511 5395.2519) (9224.6718 5402.5038)
      (9224.3511 5409.7557) (9223.3893 5416.8244) (9221.8168 5423.542) (9219.6641 5429.7557) (9216.9924 5435.2824)
      (9214.1374 5439.6031) (9190.1374 5430.5038)
    ))
    ; P2514 -- see feature_dimensions_mm.csv
    ("06_ORNAMENT" 0 (
      (9243.7405 5450.0916) (9244.0916 5447.8779) (9246.9466 5442.2595) (9251.4046 5437.8015) (9257.0229 5434.9466)
      (9263.2519 5433.9542) (9269.4809 5434.9466) (9275.0992 5437.8015) (9279.5573 5442.2595) (9282.4275 5447.8779)
      (9283.4046 5454.1069) (9282.4275 5460.3359) (9281.374 5462.3817) (9280.5954 5462.1374)
    ))
    ; P2515 -- see feature_dimensions_mm.csv
    ("06_ORNAMENT" 0 (
      (9296.1832 4412.2137) (9296.5954 4409.6336) (9297.7863 4407.2061) (9299.6794 4405.0076) (9302.1374 4403.1756)
      (9304.9771 4401.7252) (9308.0 4400.6718) (9311.0382 4399.9542) (9313.8779 4399.5115) (9316.3969 4399.1908)
      (9318.4885 4398.8702) (9320.1221 4398.3969) (9321.2824 4397.6183) (9322.0611 4396.458) (9322.5344 4394.8244)
      (9322.855 4392.7328) (9323.1756 4390.2137) (9323.6183 4387.374) (9324.3359 4384.3359) (9325.3893 4381.313)
      (9326.8397 4378.4733) (9328.6718 4376.0153) (9330.8702 4374.1221) (9333.2977 4372.9313) (9335.8779 4372.5191)
      (9338.458 4372.9313) (9340.8855 4374.1221) (9343.084 4376.0153) (9344.916 4378.4733) (9346.3664 4381.313)
      (9347.4198 4384.3359) (9348.1374 4387.374) (9348.5802 4390.2137) (9348.9008 4392.7328) (9349.2214 4394.8244)
      (9349.6947 4396.458) (9350.4733 4397.6183) (9351.6336 4398.3969) (9353.2672 4398.8702) (9355.3588 4399.1908)
      (9357.8779 4399.5115) (9360.7176 4399.9542) (9363.7557 4400.6718) (9366.7786 4401.7252) (9369.6183 4403.1756)
      (9372.0763 4405.0076) (9373.9695 4407.2061) (9375.1603 4409.6336) (9375.5725 4412.2137)
    ))
    ; P2516 -- see feature_dimensions_mm.csv
    ("06_ORNAMENT" 0 (
      (9398.9008 3999.1756) (9397.7099 3993.1756) (9398.9313 3987.0534) (9402.4122 3981.8473) (9407.6031 3978.3664)
      (9413.7405 3977.145) (9419.8779 3978.3664) (9425.0687 3981.8473) (9428.5496 3987.0534) (9429.771 3993.1756)
      (9428.5496 3999.313) (9425.0687 4004.5191) (9419.8779 4007.9847) (9413.7405 4009.2061) (9407.6031 4007.9847)
      (9402.4122 4004.5191) (9399.1298 3999.6031)
    ))
    ; P2517 -- see feature_dimensions_mm.csv
    ("06_ORNAMENT" 0 (
      (9399.1298 3999.6031) (9398.9313 3999.313) (9398.9008 3999.1756)
    ))
    ; P2518 -- see feature_dimensions_mm.csv
    ("06_ORNAMENT" 0 (
      (9398.9008 3999.1756) (9399.1298 3999.6031)
    ))
    ; P2519 -- see feature_dimensions_mm.csv
    ("06_ORNAMENT" 0 (
      (9427.0076 3832.0611) (9428.5496 3834.3817) (9429.771 3840.5038) (9428.5496 3846.6412) (9425.0687 3851.8473)
      (9419.8779 3855.313) (9413.7405 3856.5344) (9407.6031 3855.313) (9402.4122 3851.8473) (9398.9313 3846.6412)
      (9397.7099 3840.5038) (9398.9313 3834.3817) (9400.4733 3832.0611)
    ))
    ; P2520 -- see feature_dimensions_mm.csv
    ("06_ORNAMENT" 0 (
      (9450.3817 3206.1069) (9496.1832 3160.3053) (9541.9847 3206.1069)
    ))
    ; P2521 -- see feature_dimensions_mm.csv
    ("06_ORNAMENT" 1 (
      (9450.3817 3206.1069) (9404.5802 3251.9084) (9358.7786 3206.1069) (9404.5802 3160.3053)
    ))
    ; P2522 -- see feature_dimensions_mm.csv
    ("06_ORNAMENT" 0 (
      (9541.9847 3206.1069) (9496.1832 3251.9084) (9450.3817 3206.1069)
    ))
    ; P2523 -- see feature_dimensions_mm.csv
    ("06_ORNAMENT" 0 (
      (9450.3817 3099.2366) (9496.1832 3053.4351) (9541.9847 3099.2366)
    ))
    ; P2524 -- see feature_dimensions_mm.csv
    ("06_ORNAMENT" 1 (
      (9450.3817 3099.2366) (9404.5802 3145.0382) (9358.7786 3099.2366) (9404.5802 3053.4351)
    ))
    ; P2525 -- see feature_dimensions_mm.csv
    ("06_ORNAMENT" 0 (
      (9541.9847 3099.2366) (9496.1832 3145.0382) (9450.3817 3099.2366)
    ))
    ; P2526 -- see feature_dimensions_mm.csv
    ("06_ORNAMENT" 0 (
      (9450.3817 2992.3664) (9496.1832 2946.5649) (9541.9847 2992.3664)
    ))
    ; P2527 -- see feature_dimensions_mm.csv
    ("06_ORNAMENT" 1 (
      (9450.3817 2992.3664) (9404.5802 3038.1679) (9358.7786 2992.3664) (9404.5802 2946.5649)
    ))
    ; P2528 -- see feature_dimensions_mm.csv
    ("06_ORNAMENT" 0 (
      (9541.9847 2992.3664) (9496.1832 3038.1679) (9450.3817 2992.3664)
    ))
    ; P2529 -- see feature_dimensions_mm.csv
    ("06_ORNAMENT" 1 (
      (9541.9847 3206.1069) (9587.7863 3160.3053) (9633.5878 3206.1069) (9587.7863 3251.9084)
    ))
    ; P2530 -- see feature_dimensions_mm.csv
    ("06_ORNAMENT" 1 (
      (9541.9847 3099.2366) (9587.7863 3053.4351) (9633.5878 3099.2366) (9587.7863 3145.0382)
    ))
    ; P2531 -- see feature_dimensions_mm.csv
    ("06_ORNAMENT" 1 (
      (9541.9847 2992.3664) (9587.7863 2946.5649) (9633.5878 2992.3664) (9587.7863 3038.1679)
    ))
    ; P2532 -- see feature_dimensions_mm.csv
    ("06_ORNAMENT" 0 (
      (9576.626 3832.0611) (9578.1679 3834.3817) (9579.3893 3840.5038) (9578.1679 3846.6412) (9574.687 3851.8473)
      (9569.4962 3855.313) (9563.3588 3856.5344) (9557.2214 3855.313) (9552.0305 3851.8473) (9548.5496 3846.6412)
      (9547.3282 3840.5038) (9548.5496 3834.3817) (9550.0916 3832.0611)
    ))
    ; P2533 -- see feature_dimensions_mm.csv
    ("06_ORNAMENT" 0 (
      (9578.1985 3999.1756) (9578.1679 3999.313) (9577.9695 3999.6031)
    ))
    ; P2534 -- see feature_dimensions_mm.csv
    ("06_ORNAMENT" 0 (
      (9577.9695 3999.6031) (9578.1985 3999.1756)
    ))
    ; P2535 -- see feature_dimensions_mm.csv
    ("06_ORNAMENT" 0 (
      (9577.9695 3999.6031) (9574.687 4004.5191) (9569.4962 4007.9847) (9563.3588 4009.2061) (9557.2214 4007.9847)
      (9552.0305 4004.5191) (9548.5496 3999.313) (9547.3282 3993.1756) (9548.5496 3987.0534) (9552.0305 3981.8473)
      (9557.2214 3978.3664) (9563.3588 3977.145) (9569.4962 3978.3664) (9574.687 3981.8473) (9578.1679 3987.0534)
      (9579.3893 3993.1756) (9578.1985 3999.1756)
    ))
    ; P2536 -- see feature_dimensions_mm.csv
    ("06_ORNAMENT" 0 (
      (9979.2824 3999.6031) (9985.0076 4010.626) (9992.6107 4028.9771) (9998.5954 4047.9237) (10000.1069 4054.7634)
      (10005.2214 4058.1832) (10008.7023 4063.3893) (10009.9237 4069.5115) (10008.7023 4075.6489) (10005.2214 4080.855)
      (10004.7176 4081.1908) (10005.4809 4087.0229) (10006.3511 4106.8702) (10005.4809 4126.7176) (10004.5191 4134.0458)
      (10005.2214 4134.5191) (10008.7023 4139.7252) (10009.9237 4145.8473) (10008.7023 4151.9847) (10005.2214 4157.1908)
      (10000.0305 4160.6565) (9999.7252 4160.7176) (9998.5954 4165.8168) (9992.6107 4184.7634) (9985.0076 4203.1145)
      (9975.8473 4220.7328) (9965.1603 4237.4809) (9953.0687 4253.2519) (9939.6489 4267.8931) (9925.0076 4281.313)
      (9909.2366 4293.4046) (9892.4885 4304.0916) (9874.8702 4313.2519) (9856.5191 4320.855) (9837.5725 4326.8397)
      (9818.1679 4331.1298) (9798.4733 4333.7252) (9778.626 4334.5954) (9758.7786 4333.7252) (9739.084 4331.1298)
      (9719.6794 4326.8397) (9700.7328 4320.855) (9682.3817 4313.2519) (9664.7634 4304.0916) (9648.0153 4293.4046)
      (9632.2443 4281.313) (9617.6031 4267.8931) (9604.1832 4253.2519) (9592.0916 4237.4809) (9581.4046 4220.7328)
      (9572.2443 4203.1145) (9564.6412 4184.7634) (9558.6565 4165.8168) (9557.5267 4160.7176) (9557.2214 4160.6565)
      (9552.0305 4157.1908) (9548.5496 4151.9847) (9547.3282 4145.8473) (9548.5496 4139.7252) (9552.0305 4134.5191)
      (9552.7328 4134.0458) (9551.771 4126.7176) (9550.9008 4106.8702) (9551.771 4087.0229) (9552.5344 4081.1908)
      (9552.0305 4080.855) (9548.5496 4075.6489) (9547.3282 4069.5115) (9548.5496 4063.3893) (9552.0305 4058.1832)
      (9557.145 4054.7634) (9558.6565 4047.9237) (9564.6412 4028.9771) (9572.2443 4010.626) (9577.9695 3999.6031)
    ))
    ; P2537 -- see feature_dimensions_mm.csv
    ("06_ORNAMENT" 0 (
      (9578.1985 3999.1756) (9581.4046 3993.0076) (9592.0916 3976.2595) (9604.1832 3960.4885) (9617.6031 3945.8473)
      (9632.2443 3932.4275) (9648.0153 3920.3359) (9664.7634 3909.6489) (9682.3817 3900.4885) (9700.7328 3892.8855)
      (9719.6794 3886.9008) (9739.084 3882.6107) (9758.7786 3880.0153) (9778.626 3879.145) (9798.4733 3880.0153)
      (9818.1679 3882.6107) (9837.5725 3886.9008) (9856.5191 3892.8855) (9874.8702 3900.4885) (9892.4885 3909.6489)
      (9909.2366 3920.3359) (9925.0076 3932.4275) (9939.6489 3945.8473) (9953.0687 3960.4885) (9965.1603 3976.2595)
      (9975.8473 3993.0076) (9979.0534 3999.1756)
    ))
    ; P2538 -- see feature_dimensions_mm.csv
    ("06_ORNAMENT" 0 (
      (9640.3206 5478.3511) (9632.2443 5472.1527) (9617.6031 5458.7328) (9604.1832 5444.0916) (9592.0916 5428.3206)
      (9581.4046 5411.5725) (9572.2443 5393.9542) (9567.4656 5382.4427) (9563.3588 5383.2519) (9557.2214 5382.0305)
      (9552.0305 5378.5649) (9548.5496 5373.3588) (9547.3282 5367.2214) (9548.5496 5361.0992) (9552.0305 5355.8931)
      (9557.2214 5352.4122) (9557.6947 5352.3206) (9554.3664 5337.2519) (9551.771 5317.5573) (9551.0382 5300.7481)
      (9548.5496 5297.0229) (9547.3282 5290.8855) (9548.5496 5284.7634) (9551.6641 5280.0916) (9551.771 5277.8626)
      (9554.3664 5258.1679) (9558.6565 5238.7634) (9561.3588 5230.1832) (9557.2214 5229.3588) (9552.0305 5225.8931)
      (9548.5496 5220.687) (9547.3282 5214.5496) (9548.5496 5208.4275) (9552.0305 5203.2214) (9557.2214 5199.7405)
      (9563.3588 5198.5191) (9569.4962 5199.7405) (9572.1985 5201.5573) (9572.2443 5201.4656) (9581.4046 5183.8473)
      (9592.0916 5167.0992) (9604.1832 5151.3282) (9617.6031 5136.687) (9632.2443 5123.2672) (9648.0153 5111.1756)
      (9664.7634 5100.4885) (9682.3817 5091.3282) (9700.7328 5083.7252) (9719.6794 5077.7405) (9739.084 5073.4504)
      (9758.7786 5070.855) (9778.626 5069.9847) (9798.4733 5070.855) (9818.1679 5073.4504) (9837.5725 5077.7405)
      (9856.5191 5083.7252) (9874.8702 5091.3282) (9892.4885 5100.4885) (9909.2366 5111.1756) (9925.0076 5123.2672)
      (9939.6489 5136.687) (9953.0687 5151.3282) (9965.1603 5167.0992) (9975.8473 5183.8473) (9985.0076 5201.4656)
      (9985.0534 5201.5573) (9987.7557 5199.7405) (9993.8931 5198.5191) (10000.0305 5199.7405) (10005.2214 5203.2214)
      (10008.7023 5208.4275) (10009.9237 5214.5496) (10008.7023 5220.687) (10005.2214 5225.8931) (10000.0305 5229.3588)
      (9995.8931 5230.1832) (9998.5954 5238.7634) (10002.8855 5258.1679) (10005.4809 5277.8626) (10005.5878 5280.0916)
      (10006.626 5281.6489)
    ))
    ; P2539 -- see feature_dimensions_mm.csv
    ("06_ORNAMENT" 0 (
      (9678.1221 5467.6336) (9666.5954 5471.0687)
    ))
    ; P2540 -- see feature_dimensions_mm.csv
    ("06_ORNAMENT" 0 (
      (9695.7252 5462.3817) (9678.1221 5467.6336)
    ))
    ; P2541 -- see feature_dimensions_mm.csv
    ("06_ORNAMENT" 0 (
      (9678.1221 5467.6336) (9665.3435 5459.4962) (9651.6794 5449.0076) (9645.0229 5442.9008) (9642.5649 5442.1374)
      (9639.8779 5440.687) (9637.5573 5438.7786) (9635.6489 5436.458) (9634.1985 5433.771) (9633.4351 5431.313)
      (9627.3282 5424.6565) (9616.8397 5410.9924) (9607.5878 5396.458) (9599.6336 5381.1756) (9593.0382 5365.2519)
      (9587.8626 5348.8244) (9584.1374 5332.0) (9581.8779 5314.916) (9581.4809 5305.8931) (9580.3053 5303.6336)
      (9579.4198 5300.7023) (9579.1145 5297.7099) (9579.4198 5294.7176) (9580.3053 5291.7863) (9581.4809 5289.5267)
      (9581.8779 5280.5038) (9584.1374 5263.4198) (9587.8626 5246.5954) (9593.0382 5230.1679) (9599.6336 5214.2443)
      (9607.5878 5198.9618) (9616.8397 5184.4275) (9627.3282 5170.7634) (9633.4351 5164.1069) (9634.1985 5161.6489)
      (9635.6489 5158.9618) (9637.5573 5156.6412) (9639.8779 5154.7328) (9642.5649 5153.2824) (9645.0229 5152.5191)
      (9651.6794 5146.4122) (9665.3435 5135.9237) (9679.8779 5126.6718) (9695.1603 5118.7176) (9711.084 5112.1221)
      (9727.5115 5106.9466) (9744.3359 5103.2214) (9761.4198 5100.9618) (9770.4427 5100.5649) (9772.7023 5099.3893)
      (9775.6336 5098.4885) (9778.626 5098.1985) (9781.6183 5098.4885) (9784.5496 5099.3893) (9786.8092 5100.5649)
      (9795.8321 5100.9618) (9812.916 5103.2214) (9829.7405 5106.9466) (9846.1679 5112.1221) (9862.0916 5118.7176)
      (9877.374 5126.6718) (9891.9084 5135.9237) (9905.5725 5146.4122) (9912.229 5152.5191) (9914.687 5153.2824)
      (9917.374 5154.7328) (9919.6947 5156.6412) (9921.6031 5158.9618) (9923.0534 5161.6489) (9923.8168 5164.1069)
      (9929.9237 5170.7634) (9940.4122 5184.4275) (9949.6641 5198.9618) (9957.6183 5214.2443) (9964.2137 5230.1679)
      (9969.3893 5246.5954) (9973.1145 5263.4198) (9975.374 5280.5038) (9975.771 5289.5267) (9976.9466 5291.7863)
      (9977.8473 5294.7176) (9978.1374 5297.7099) (9977.8473 5300.7023) (9976.9466 5303.6336) (9975.771 5305.8931)
      (9975.374 5314.916) (9974.6718 5320.2443)
    ))
    ; P2542 -- see feature_dimensions_mm.csv
    ("06_ORNAMENT" 1 (
      (9695.7252 5462.3817) (9694.6718 5460.3359) (9693.6947 5454.1069) (9694.6718 5447.8779) (9697.542 5442.2595)
      (9702.0 5437.8015) (9707.6183 5434.9466) (9713.8473 5433.9542) (9720.0763 5434.9466) (9725.6947 5437.8015)
      (9730.1527 5442.2595) (9733.0076 5447.8779) (9733.3588 5450.0916) (9726.7328 5452.4122) (9696.5038 5462.1374)
    ))
    ; P2543 -- see feature_dimensions_mm.csv
    ("06_ORNAMENT" 0 (
      (9786.9618 5430.5038) (9762.9618 5439.6031) (9760.1069 5435.2824) (9757.4351 5429.7557) (9755.2824 5423.542)
      (9753.7099 5416.8244) (9752.7481 5409.7557) (9752.4275 5402.5038) (9752.7481 5395.2519) (9753.7099 5388.1832)
      (9755.2824 5381.4656) (9757.4351 5375.2519) (9760.1069 5369.7252) (9763.2214 5365.0076) (9766.7328 5361.2061)
      (9770.5344 5358.4275) (9774.5344 5356.7176) (9778.626 5356.1527) (9782.7176 5356.7176) (9786.7176 5358.4275)
      (9790.5191 5361.2061) (9794.0305 5365.0076) (9797.145 5369.7252) (9799.8168 5375.2519) (9801.9695 5381.4656)
      (9803.542 5388.1832) (9804.5038 5395.2519) (9804.8244 5402.5038) (9804.5038 5409.7557) (9803.542 5416.8244)
      (9801.9695 5423.542) (9801.6641 5424.4275)
    ))
    ; P2544 -- see feature_dimensions_mm.csv
    ("06_ORNAMENT" 0 (
      (9850.3206 5402.7176) (9845.2366 5399.5573) (9839.5573 5395.2366) (9834.1985 5390.3359) (9829.2977 5384.9771)
      (9824.9771 5379.2977) (9821.3435 5373.4351) (9818.4733 5367.5267) (9816.458 5361.7405) (9815.3282 5356.1832)
      (9815.1145 5351.0229) (9815.8321 5346.3664) (9817.4504 5342.3359) (9819.9542 5339.0382) (9823.2519 5336.5344)
      (9827.2824 5334.916) (9831.9389 5334.1985) (9837.0992 5334.4122) (9842.6565 5335.542) (9848.4427 5337.5573)
      (9854.3511 5340.4275) (9860.2137 5344.0611) (9865.8931 5348.3817) (9871.2519 5353.2824) (9876.1527 5358.6412)
      (9880.4733 5364.3206) (9884.1069 5370.1832) (9886.9771 5376.0916) (9889.0076 5381.8931) (9889.0992 5382.3511)
      (9872.7634 5391.4656)
    ))
    ; P2545 -- see feature_dimensions_mm.csv
    ("06_ORNAMENT" 0 (
      (9876.3359 4412.2137) (9876.7481 4409.6336) (9877.9389 4407.2061) (9879.8321 4405.0076) (9882.2901 4403.1756)
      (9885.1298 4401.7252) (9888.1527 4400.6718) (9891.1908 4399.9542) (9894.0305 4399.5115) (9896.5496 4399.1908)
      (9898.6412 4398.8702) (9900.2748 4398.3969) (9901.4351 4397.6183) (9902.2137 4396.458) (9902.687 4394.8244)
      (9903.0076 4392.7328) (9903.3282 4390.2137) (9903.771 4387.374) (9904.4885 4384.3359) (9905.542 4381.313)
      (9906.9924 4378.4733) (9908.8244 4376.0153) (9911.0229 4374.1221) (9913.4504 4372.9313) (9916.0305 4372.5191)
      (9918.6107 4372.9313) (9921.0382 4374.1221) (9923.2366 4376.0153) (9925.0687 4378.4733) (9926.5191 4381.313)
      (9927.5725 4384.3359) (9928.2901 4387.374) (9928.7328 4390.2137) (9929.0534 4392.7328) (9929.374 4394.8244)
      (9929.8473 4396.458) (9930.626 4397.6183) (9931.7863 4398.3969) (9933.4198 4398.8702) (9935.5115 4399.1908)
      (9938.0305 4399.5115) (9940.8702 4399.9542) (9943.9084 4400.6718) (9946.9313 4401.7252) (9949.771 4403.1756)
      (9952.229 4405.0076) (9954.1221 4407.2061) (9955.313 4409.6336) (9955.7252 4412.2137)
    ))
    ; P2546 -- see feature_dimensions_mm.csv
    ("06_ORNAMENT" 0 (
      (9915.4962 5366.458) (9914.8702 5362.4885) (9915.8626 5356.2595) (9918.7176 5350.6412) (9923.1756 5346.1832)
      (9928.7939 5343.3282) (9935.0229 5342.3359) (9941.2519 5343.3282) (9945.6336 5345.5573) (9923.7405 5361.2672)
    ))
    ; P2547 -- see feature_dimensions_mm.csv
    ("06_ORNAMENT" 0 (
      (9979.0534 3999.1756) (9977.8626 3993.1756) (9979.084 3987.0534) (9982.5649 3981.8473) (9987.7557 3978.3664)
      (9993.8931 3977.145) (10000.0305 3978.3664) (10005.2214 3981.8473) (10008.7023 3987.0534) (10009.9237 3993.1756)
      (10008.7023 3999.313) (10005.2214 4004.5191) (10000.0305 4007.9847) (9993.8931 4009.2061) (9987.7557 4007.9847)
      (9982.5649 4004.5191) (9979.2824 3999.6031)
    ))
    ; P2548 -- see feature_dimensions_mm.csv
    ("06_ORNAMENT" 0 (
      (9979.2824 3999.6031) (9979.084 3999.313) (9979.0534 3999.1756)
    ))
    ; P2549 -- see feature_dimensions_mm.csv
    ("06_ORNAMENT" 0 (
      (9979.0534 3999.1756) (9979.2824 3999.6031)
    ))
    ; P2550 -- see feature_dimensions_mm.csv
    ("06_ORNAMENT" 0 (
      (10007.1603 3832.0611) (10008.7023 3834.3817) (10009.9237 3840.5038) (10008.7023 3846.6412) (10005.2214 3851.8473)
      (10000.0305 3855.313) (9993.8931 3856.5344) (9987.7557 3855.313) (9982.5649 3851.8473) (9979.084 3846.6412)
      (9977.8626 3840.5038) (9979.084 3834.3817) (9980.626 3832.0611)
    ))
    ; P2551 -- see feature_dimensions_mm.csv
    ("06_ORNAMENT" 0 (
      (9988.2901 5306.0763) (9988.229 5306.1527) (9988.1985 5306.1832)
    ))
    ; P2552 -- see feature_dimensions_mm.csv
    ("06_ORNAMENT" 0 (
      (9998.2748 5293.8779) (9993.8473 5299.2824)
    ))
    ; P2553 -- see feature_dimensions_mm.csv
    ("06_ORNAMENT" 0 (
      (10687.0229 5362.1832) (10698.8702 5366.3817) (10709.9237 5375.2672) (10716.2443 5388.5038) (10719.8015 5406.0916)
      (10721.0687 5426.8244) (10720.5191 5449.4656) (10718.6565 5472.7939) (10715.9389 5495.5878) (10712.8702 5516.6107)
      (10709.9237 5534.6565) (10706.7176 5550.626) (10702.626 5566.0916) (10697.7863 5580.7786) (10692.2901 5594.4275)
      (10687.0229 5605.2519) (10687.0229 5465.6489)
    ))
    ; P2554 -- see feature_dimensions_mm.csv
    ("06_ORNAMENT" 0 (
      (10687.0229 5079.2519) (10700.4885 5077.3588) (10725.0992 5051.084) (10704.5649 5064.0458) (10687.0229 5074.3664)
    ))
    ; P2555 -- see feature_dimensions_mm.csv
    ("06_ORNAMENT" 0 (
      (10687.0229 5079.2519) (10687.0229 5074.3664)
    ))
    ; P2556 -- see feature_dimensions_mm.csv
    ("06_ORNAMENT" 0 (
      (10687.0229 3968.3359) (10706.3969 3967.9847) (10711.5725 3959.9237) (10724.7786 3940.8397) (10739.0076 3921.7252)
      (10754.0611 3902.8702) (10769.8168 3884.5496) (10786.1069 3867.0382) (10788.7328 3864.4733) (10790.855 3855.4198)
      (10793.9084 3846.5649) (10797.6183 3838.3053) (10801.771 3830.916) (10806.1069 3824.7328) (10811.1603 3819.4351)
      (10817.4046 3814.5954) (10824.4885 3810.3664) (10832.0305 3806.8702) (10839.6794 3804.229) (10847.084 3802.5802)
      (10853.8779 3802.0458) (10859.6947 3802.7481) (10864.2443 3804.8397) (10870.229 3801.5267) (10867.8168 3807.4962)
      (10870.1679 3809.3893) (10875.1298 3814.9466) (10879.6641 3821.374) (10883.5573 3828.229) (10886.626 3835.0382)
      (10888.6565 3841.3588) (10889.4656 3846.7176) (10888.2443 3851.4656) (10884.8397 3856.1985) (10880.0305 3860.8092)
      (10874.5802 3865.1908) (10869.2519 3869.2519) (10864.8092 3872.8855) (10862.0305 3875.9847) (10861.6794 3878.4733)
      (10864.0 3880.5649) (10868.3511 3882.458) (10874.1985 3884.0) (10881.0382 3885.0382) (10888.2901 3885.4046)
      (10895.4504 3884.9466) (10901.9695 3883.4962) (10907.3282 3880.916) (10911.9695 3876.9924) (10916.5954 3871.771)
      (10921.0687 3865.5267) (10925.1908 3858.4733) (10928.8244 3850.8702) (10931.8015 3842.9618) (10933.9542 3834.9771)
      (10935.1145 3827.1756) (10935.4962 3819.1603) (10935.3435 3810.5344) (10934.5496 3801.5267) (10933.0076 3792.3664)
      (10930.6107 3783.2824) (10927.2519 3774.5038) (10922.8397 3766.2595) (10917.2519 3758.7786) (10908.5496 3751.7405)
      (10895.9847 3744.8092) (10881.2672 3738.1374) (10866.1527 3731.9084) (10852.3206 3726.2901) (10841.5267 3721.4504)
      (10835.4656 3717.5725) (10835.8779 3714.8092) (10844.4885 3712.5496) (10860.3969 3710.3817) (10881.374 3708.7328)
      (10905.2214 3708.0916) (10929.6947 3708.8855) (10952.5954 3711.6031) (10971.6794 3716.6718) (10984.7328 3724.5802)
      (10992.2137 3736.3511) (10996.4122 3751.9847) (10997.9084 3770.4122) (10997.2672 3790.5344) (10995.0534 3811.2672)
      (10991.8473 3831.5267) (10988.2137 3850.2137) (10984.7328 3866.2595) (10980.9466 3880.458) (10976.1069 3894.1985)
      (10970.3817 3907.2519) (10963.8931 3919.3893) (10956.7786 3930.3817) (10949.1908 3940.0) (10941.2672 3948.0153)
      (10933.1298 3954.1985) (10924.4275 3958.3969) (10914.8702 3960.7634) (10910.1374 3961.1145) (10932.3817 3963.8321)
      (10954.3969 3969.8473) (10969.4656 3979.2366) (10978.0916 3993.2061) (10982.9313 4011.7863) (10984.6565 4033.6641)
      (10983.9237 4057.5573) (10981.374 4082.1832) (10977.6794 4106.229) (10973.4962 4128.4275) (10969.4656 4147.4809)
      (10965.084 4164.3359) (10959.5115 4180.6565) (10952.9008 4196.1527) (10945.4198 4210.5649) (10937.2214 4223.6183)
      (10928.458 4235.0534) (10919.313 4244.5649) (10909.9237 4251.9084) (10899.8779 4256.9008) (10888.855 4259.7099)
      (10877.1145 4260.6107) (10864.9771 4259.8779) (10861.0534 4259.2214) (10862.5191 4277.9389) (10861.7863 4301.8321)
      (10859.2366 4326.458) (10855.542 4350.5038) (10851.3588 4372.7023) (10847.3282 4391.7557) (10842.9466 4408.6107)
      (10837.8168 4423.6794) (10855.3588 4449.771) (10873.9542 4480.0763) (10891.6947 4511.8931) (10908.2901 4544.8092)
      (10923.4198 4578.458) (10936.7786 4612.4427) (10948.0611 4646.3969) (10956.9771 4679.9084) (10963.2214 4712.6107)
      (10966.458 4744.1221) (10966.4275 4768.3359) (10973.2824 4782.4427) (10967.6641 4780.2595) (10980.1527 4790.8397)
      (10963.6183 4791.374) (10987.0229 4799.2366) (10966.3511 4807.8931) (10993.8931 4807.6336) (10972.7328 4824.2595)
      (11000.7634 4816.0305) (10983.4351 4837.4962) (11007.6336 4824.4275) (10985.3893 4863.9084) (10958.7023 4904.4885)
      (10928.2137 4945.6947) (10894.5344 4987.084) (10858.2901 5028.2137) (10820.0916 5068.6412) (10810.3206 5078.3511)
      (10832.2595 5084.3511) (10847.3282 5093.7405) (10855.9542 5107.7099) (10860.7939 5126.2901) (10862.5191 5148.1679)
      (10861.7863 5172.0611) (10859.2366 5196.687) (10855.542 5220.7328) (10851.3588 5242.9313) (10847.3282 5261.9847)
      (10842.9466 5278.8397) (10837.374 5295.1603) (10830.7634 5310.6565) (10823.2824 5325.0687) (10815.084 5338.1221)
      (10806.3206 5349.5573) (10797.1756 5359.0687) (10787.7863 5366.4122) (10777.7405 5371.4046) (10766.7176 5374.2137)
      (10754.9771 5375.1145) (10742.8397 5374.3817) (10730.5954 5372.3053) (10718.5496 5369.1298) (10706.9771 5365.145)
      (10696.1832 5360.6107) (10687.0229 5355.8168) (10687.0229 5192.0763) (10687.0229 5186.7023) (10687.0229 5092.3053)
      (10687.0229 5092.2748) (10687.0229 5079.2519)
    ))
    ; P2557 -- see feature_dimensions_mm.csv
    ("06_ORNAMENT" 0 (
      (10687.0229 5074.3664) (10687.0229 4982.9466)
    ))
    ; P2558 -- see feature_dimensions_mm.csv
    ("06_ORNAMENT" 0 (
      (10687.0229 4982.9466) (10712.5649 4964.1832) (10749.2824 4938.9771) (10719.5267 4949.6489) (10687.0229 4960.0458)
    ))
    ; P2559 -- see feature_dimensions_mm.csv
    ("06_ORNAMENT" 0 (
      (10687.0229 4982.9466) (10687.0229 4960.0458)
    ))
    ; P2560 -- see feature_dimensions_mm.csv
    ("06_ORNAMENT" 0 (
      (10687.0229 4960.0458) (10687.0229 4877.2366)
    ))
    ; P2561 -- see feature_dimensions_mm.csv
    ("06_ORNAMENT" 0 (
      (10687.0229 4877.2366) (10702.6412 4870.8702) (10746.5191 4854.7634) (10761.6794 4849.8473) (10755.1756 4850.3969)
      (10712.5191 4852.2595) (10687.0229 4852.3817)
    ))
    ; P2562 -- see feature_dimensions_mm.csv
    ("06_ORNAMENT" 0 (
      (10687.0229 4877.2366) (10687.0229 4852.3817)
    ))
    ; P2563 -- see feature_dimensions_mm.csv
    ("06_ORNAMENT" 0 (
      (10687.0229 4852.3817) (10687.0229 4774.9313)
    ))
    ; P2564 -- see feature_dimensions_mm.csv
    ("06_ORNAMENT" 0 (
      (10687.0229 4774.9313) (10718.6412 4772.0611) (10760.8092 4769.8931) (10797.542 4769.5267) (10790.2443 4767.7405)
      (10750.1832 4755.9847) (10710.5954 4742.5191) (10687.0229 4733.4504)
    ))
    ; P2565 -- see feature_dimensions_mm.csv
    ("06_ORNAMENT" 0 (
      (10687.0229 4774.9313) (10687.0229 4733.4504)
    ))
    ; P2566 -- see feature_dimensions_mm.csv
    ("06_ORNAMENT" 0 (
      (10687.0229 4733.4504) (10687.0229 4653.9542)
    ))
    ; P2567 -- see feature_dimensions_mm.csv
    ("06_ORNAMENT" 0 (
      (10687.0229 4653.9542) (10687.0229 4570.3664)
    ))
    ; P2568 -- see feature_dimensions_mm.csv
    ("06_ORNAMENT" 0 (
      (10687.0229 4653.9542) (10705.5115 4658.5344) (10745.1908 4669.9389) (10784.4427 4682.9313) (10822.7023 4697.4351)
      (10823.5725 4697.8015) (10810.9924 4688.3053) (10779.5267 4662.1527) (10749.1756 4634.626) (10720.2595 4606.2137)
      (10693.0992 4577.3588) (10687.0229 4570.3664)
    ))
    ; P2569 -- see feature_dimensions_mm.csv
    ("06_ORNAMENT" 0 (
      (10687.0229 4570.3664) (10687.0229 4491.6031)
    ))
    ; P2570 -- see feature_dimensions_mm.csv
    ("06_ORNAMENT" 1 (
      (10687.0229 4491.6031) (10714.5954 4509.3893) (10746.5038 4531.7863) (10778.3359 4555.9542) (10809.6183 4581.6489)
      (10839.8473 4608.5954) (10858.229 4626.4885) (10846.8092 4603.4504) (10831.8168 4569.2672) (10818.5038 4534.8397)
      (10806.9313 4500.626) (10802.0305 4483.7863) (10797.1756 4488.8397) (10787.7863 4496.1832) (10777.7405 4501.1756)
      (10766.7176 4503.9847) (10754.9771 4504.8855) (10742.8397 4504.1527) (10730.5954 4502.0763) (10718.5496 4498.9008)
      (10706.9771 4494.916) (10696.1832 4490.3817) (10687.0229 4485.5878)
    ))
    ; P2571 -- see feature_dimensions_mm.csv
    ("06_ORNAMENT" 0 (
      (10687.0229 4316.4733) (10688.5038 4316.1374) (10696.3359 4315.4962) (10703.0534 4316.3359) (10709.1145 4319.2214)
      (10715.1298 4324.229) (10720.8702 4330.8244) (10726.0916 4338.458) (10730.5954 4346.5954) (10734.1374 4354.687)
      (10736.4733 4362.1832) (10737.4046 4368.5496) (10736.0 4374.1985) (10732.0763 4379.8168) (10726.5191 4385.2824)
      (10720.229 4390.4885) (10714.0763 4395.2977) (10708.9618 4399.6183) (10705.7557 4403.313) (10705.3435 4406.2595)
      (10708.0153 4408.7481) (10713.0382 4410.9924) (10719.8015 4412.8244) (10727.6794 4414.0611) (10736.0458 4414.4885)
      (10744.3053 4413.9389) (10751.8321 4412.229) (10758.0153 4409.1603) (10763.374 4404.4885) (10768.7176 4398.3053)
      (10773.8626 4390.8855) (10778.626 4382.5038) (10780.3359 4378.8092) (10780.0305 4376.458) (10778.626 4351.145)
      (10787.2061 4360.4275) (10788.7328 4354.6107) (10790.0763 4345.3435) (10790.5191 4335.8321) (10790.3511 4325.5878)
      (10789.4198 4314.8855) (10787.6489 4304.0) (10784.8702 4293.2214) (10781.0076 4282.7939) (10775.9084 4273.0076)
      (10769.4656 4264.1221) (10759.4198 4255.771) (10744.916 4247.5267) (10727.9542 4239.6183) (10710.5038 4232.2137)
      (10694.5496 4225.542) (10687.8168 4222.4427) (10687.0229 4223.4809)
    ))
    ; P2572 -- see feature_dimensions_mm.csv
    ("06_ORNAMENT" 0 (
      (10687.0229 4100.229) (10689.6031 4096.6565) (10687.0229 4099.2061)
    ))
    ; P2573 -- see feature_dimensions_mm.csv
    ("06_ORNAMENT" 0 (
      (10687.0229 4048.1374) (10687.0229 4076.7328) (10688.5038 4078.9466) (10691.1603 4084.4733) (10692.2137 4089.1603)
      (10690.6107 4093.313) (10687.0229 4096.6718)
    ))
    ; P2574 -- see feature_dimensions_mm.csv
    ("06_ORNAMENT" 0 (
      (10687.0229 4048.1374) (10694.0 4037.7099) (10711.771 4012.6718) (10716.8244 4005.9389) (10710.4122 4003.5725)
      (10700.5038 4011.3588) (10687.0229 4020.9313)
    ))
    ; P2575 -- see feature_dimensions_mm.csv
    ("06_ORNAMENT" 0 (
      (10687.0229 4048.1374) (10687.0229 4020.9313)
    ))
    ; P2576 -- see feature_dimensions_mm.csv
    ("06_ORNAMENT" 0 (
      (10687.0229 4020.9313) (10687.0229 4000.1527)
    ))
    ; P2577 -- see feature_dimensions_mm.csv
    ("06_ORNAMENT" 0 (
      (10687.0229 4000.1527) (10688.7328 3996.9466) (10689.0382 3996.4427) (10687.0229 3995.8321)
    ))
    ; P2578 -- see feature_dimensions_mm.csv
    ("06_ORNAMENT" 0 (
      (10687.0229 4000.1527) (10687.0229 3995.8321)
    ))
    ; P2579 -- see feature_dimensions_mm.csv
    ("06_ORNAMENT" 0 (
      (10687.0229 3995.8321) (10687.0229 3968.3359)
    ))
    ; P2580 -- see feature_dimensions_mm.csv
    ("06_ORNAMENT" 0 (
      (10687.0229 3968.3359) (10687.0229 3740.458) (10687.0229 3679.3893) (10687.0229 3664.1221) (10687.0229 3633.5878)
      (10717.5573 3633.5878) (11053.4351 3633.5878) (11053.4351 3679.3893) (11053.4351 4473.2824) (11129.771 4473.2824)
    ))
    ; P2581 -- see feature_dimensions_mm.csv
    ("06_ORNAMENT" 0 (
      (10891.771 6015.2672) (10889.4351 6010.5344) (10884.2748 6003.0534) (10876.2443 5996.0153) (10864.6412 5989.084)
      (10851.0687 5982.4122) (10837.0992 5976.1832) (10824.3359 5970.5649) (10814.3664 5965.7252) (10808.7786 5961.8473)
      (10809.1603 5959.084) (10817.0992 5956.8244) (10831.7863 5954.6565) (10851.1603 5953.0076) (10873.1756 5952.3664)
      (10895.7557 5953.1603) (10916.9008 5955.8779) (10934.5191 5960.9466) (10946.5649 5968.855) (10953.4656 5980.626)
      (10957.3435 5996.2595) (10958.7176 6014.687) (10958.1374 6034.8092) (10956.0916 6055.542) (10953.1298 6075.8015)
      (10949.7863 6094.4885) (10946.5649 6110.5344) (10943.0687 6124.7328) (10938.6107 6138.4733) (10933.313 6151.5267)
      (10931.2977 6155.6183)
    ))
    ; P2582 -- see feature_dimensions_mm.csv
    ("06_ORNAMENT" 0 (
      (11527.8321 4412.2137) (11343.5115 4412.2137) (11312.9771 4412.2137) (11236.6412 4412.2137) (11129.771 4412.2137)
      (11114.5038 4412.2137)
    ))
    ; P2583 -- see feature_dimensions_mm.csv
    ("06_ORNAMENT" 0 (
      (11394.7939 4123.6489) (11394.7328 4122.1374) (11395.8168 4097.3282) (11399.0534 4072.7023) (11404.4275 4048.458)
      (11411.8931 4024.7786) (11421.4046 4001.8321) (11432.8702 3979.8015) (11446.2137 3958.8702) (11461.3282 3939.1603)
      (11478.1069 3920.855) (11496.4122 3904.0763) (11516.1221 3888.9618) (11537.0687 3875.6183) (11559.084 3864.1527)
      (11582.0305 3854.6412) (11605.7099 3847.1756) (11629.9542 3841.8015) (11654.5802 3838.5649) (11679.3893 3837.4809)
      (11704.1985 3838.5649) (11728.8244 3841.8015) (11753.0687 3847.1756) (11776.7481 3854.6412) (11799.6947 3864.1527)
      (11821.7252 3875.6183) (11842.6565 3888.9618) (11862.3664 3904.0763) (11880.6718 3920.855) (11897.4504 3939.1603)
      (11912.5649 3958.8702) (11925.9084 3979.8015) (11937.374 4001.8321) (11946.8855 4024.7786) (11954.3511 4048.458)
      (11959.7252 4072.7023) (11962.9618 4097.3282) (11964.0458 4122.1374) (11963.9847 4123.6489)
    ))
    ; P2584 -- see feature_dimensions_mm.csv
    ("06_ORNAMENT" 0 (
      (11395.2824 4134.5802) (11394.9618 4136.1679) (11391.4809 4141.3588) (11386.2901 4144.8397) (11380.1527 4146.0611)
      (11374.0153 4144.8397) (11368.8244 4141.3588) (11365.3435 4136.1679) (11364.1221 4130.0305) (11365.3435 4123.8931)
      (11368.8244 4118.687) (11374.0153 4115.2214) (11380.1527 4114.0) (11386.2901 4115.2214) (11391.4809 4118.687)
      (11394.7939 4123.6489)
    ))
    ; P2585 -- see feature_dimensions_mm.csv
    ("06_ORNAMENT" 0 (
      (11395.2824 4134.5802) (11394.7939 4123.6489)
    ))
    ; P2586 -- see feature_dimensions_mm.csv
    ("06_ORNAMENT" 0 (
      (11394.7939 4123.6489) (11394.9618 4123.8931) (11396.1832 4130.0305) (11395.2824 4134.5802)
    ))
    ; P2587 -- see feature_dimensions_mm.csv
    ("06_ORNAMENT" 0 (
      (11666.5954 4406.229) (11654.5802 4405.7099) (11629.9542 4402.4733) (11605.7099 4397.0992) (11582.0305 4389.6336)
      (11559.084 4380.1221) (11537.0687 4368.6565) (11516.1221 4355.313) (11496.4122 4340.1985) (11478.1069 4323.4198)
      (11461.3282 4305.1145) (11446.2137 4285.4046) (11432.8702 4264.458) (11421.4046 4242.4427) (11411.8931 4219.4962)
      (11404.4275 4195.8168) (11399.0534 4171.5725) (11395.8168 4146.9466) (11395.2824 4134.5802)
    ))
    ; P2588 -- see feature_dimensions_mm.csv
    ("06_ORNAMENT" 0 (
      (11395.6183 4737.8931) (11394.7328 4717.5573) (11395.8168 4692.7481) (11399.0534 4668.1221) (11404.4275 4643.8779)
      (11411.8931 4620.1985) (11421.4046 4597.2519) (11432.8702 4575.2214) (11446.2137 4554.2901) (11461.3282 4534.5802)
      (11478.1069 4516.2748) (11496.4122 4499.4962) (11516.1221 4484.3817) (11533.542 4473.2824)
    ))
    ; P2589 -- see feature_dimensions_mm.csv
    ("06_ORNAMENT" 0 (
      (11395.8321 4742.4885) (11394.9618 4746.855) (11391.4809 4752.0458) (11386.2901 4755.5267) (11380.1527 4756.7481)
      (11374.0153 4755.5267) (11368.8244 4752.0458) (11365.3435 4746.855) (11364.1221 4740.7176) (11365.3435 4734.5802)
      (11368.8244 4729.374) (11374.0153 4725.9084) (11380.1527 4724.687) (11386.2901 4725.9084) (11391.4809 4729.374)
      (11394.9618 4734.5802) (11395.6183 4737.8931)
    ))
    ; P2590 -- see feature_dimensions_mm.csv
    ("06_ORNAMENT" 0 (
      (11395.8321 4742.4885) (11395.8168 4742.3664) (11395.6183 4737.8931)
    ))
    ; P2591 -- see feature_dimensions_mm.csv
    ("06_ORNAMENT" 0 (
      (11395.6183 4737.8931) (11396.1832 4740.7176) (11395.8321 4742.4885)
    ))
    ; P2592 -- see feature_dimensions_mm.csv
    ("06_ORNAMENT" 0 (
      (11666.5954 5001.6489) (11654.5802 5001.1298) (11629.9542 4997.8931) (11605.7099 4992.5191) (11582.0305 4985.0534)
      (11559.084 4975.542) (11537.0687 4964.0763) (11516.1221 4950.7328) (11496.4122 4935.6183) (11478.1069 4918.8397)
      (11461.3282 4900.5344) (11446.2137 4880.8244) (11432.8702 4859.8779) (11421.4046 4837.8626) (11411.8931 4814.916)
      (11404.4275 4791.2366) (11399.0534 4766.9924) (11395.8321 4742.4885)
    ))
    ; P2593 -- see feature_dimensions_mm.csv
    ("06_ORNAMENT" 0 (
      (11403.2519 5330.2901) (11395.0992 5321.2519) (11394.7328 5312.9771) (11395.8168 5288.1679) (11399.0534 5263.542)
      (11404.4275 5239.2977) (11411.8931 5215.6183) (11421.4046 5192.6718) (11432.8702 5170.6412) (11446.2137 5149.7099)
      (11461.3282 5130.0) (11478.1069 5111.6947) (11496.4122 5094.916) (11516.1221 5079.8015) (11537.0687 5066.458)
      (11559.084 5054.9924) (11582.0305 5045.4809) (11605.7099 5038.0153) (11629.9542 5032.6412) (11644.1069 5030.7786)
      (11643.1908 5030.1069) (11641.2977 5027.9084) (11640.1069 5025.4809) (11639.6947 5022.9008) (11640.1069 5020.3206)
      (11641.2977 5017.8931) (11643.1908 5015.6947) (11645.6489 5013.8626) (11648.4885 5012.4122) (11651.5115 5011.3588)
      (11654.5496 5010.6412) (11657.3893 5010.1985) (11659.9084 5009.8779) (11662.0 5009.5573) (11663.6336 5009.084)
      (11664.7939 5008.3053) (11665.5725 5007.145) (11666.0458 5005.5115) (11666.3664 5003.4198) (11666.5954 5001.6489)
    ))
    ; P2594 -- see feature_dimensions_mm.csv
    ("06_ORNAMENT" 0 (
      (11454.7176 5372.6565) (11437.0382 5359.2824) (11436.2748 5355.8473) (11433.4656 5334.4885) (11432.9618 5323.2061)
      (11431.4809 5320.3664) (11430.3664 5316.7176) (11430.0 5312.9771) (11430.3664 5309.2366) (11431.4809 5305.5878)
      (11432.9618 5302.7481) (11433.4656 5291.4656) (11436.2748 5270.1069) (11440.9313 5249.084) (11447.4046 5228.5496)
      (11455.6489 5208.6412) (11465.5878 5189.542) (11477.1603 5171.374) (11490.2748 5154.2901) (11497.9084 5145.9695)
      (11498.855 5142.9008) (11500.6565 5139.542) (11503.0382 5136.626) (11505.9542 5134.2443) (11509.313 5132.4427)
      (11512.3817 5131.4962) (11520.7023 5123.8626) (11537.7863 5110.7481) (11555.9542 5099.1756) (11575.0534 5089.2366)
      (11594.9618 5080.9924) (11615.4962 5074.5191) (11636.5191 5069.8626) (11657.8779 5067.0534) (11669.1603 5066.5496)
      (11672.0 5065.0687) (11675.6489 5063.9542) (11679.3893 5063.5878) (11683.1298 5063.9542) (11686.7786 5065.0687)
      (11689.6183 5066.5496) (11700.9008 5067.0534) (11722.2595 5069.8626) (11743.2824 5074.5191) (11763.8168 5080.9924)
      (11783.7252 5089.2366) (11802.8244 5099.1756) (11820.9924 5110.7481) (11838.0763 5123.8626) (11846.3969 5131.4962)
      (11849.4656 5132.4427) (11852.8244 5134.2443) (11855.7405 5136.626) (11858.1221 5139.542) (11859.9237 5142.9008)
      (11860.8702 5145.9695) (11868.5038 5154.2901) (11881.6183 5171.374) (11893.1908 5189.542) (11903.1298 5208.6412)
      (11911.374 5228.5496) (11917.8473 5249.084) (11922.5038 5270.1069) (11925.313 5291.4656) (11925.8168 5302.7481)
      (11927.2977 5305.5878) (11928.4122 5309.2366) (11928.7786 5312.9771) (11928.4122 5316.7176) (11927.2977 5320.3664)
      (11925.8168 5323.2061) (11925.313 5334.4885) (11922.5038 5355.8473) (11917.8473 5376.8702) (11911.374 5397.4046)
      (11903.1298 5417.313) (11893.1908 5436.4122) (11881.6183 5454.5802) (11868.5038 5471.6641) (11860.8702 5479.9847)
      (11859.9237 5483.0534) (11858.1221 5486.4122) (11855.7405 5489.3282) (11852.8244 5491.7099) (11849.4656 5493.5115)
      (11846.3969 5494.458) (11838.0763 5502.0916) (11820.9924 5515.2061) (11812.5191 5520.5954)
    ))
    ; P2595 -- see feature_dimensions_mm.csv
    ("06_ORNAMENT" 0 (
      (11463.9695 5378.687) (11469.084 5373.5725) (11476.1069 5370.0) (11483.8931 5368.7634) (11491.6794 5370.0)
      (11498.7023 5373.5725) (11504.2748 5379.145) (11507.8473 5386.1679) (11509.084 5393.9542) (11507.8473 5401.7405)
      (11506.4122 5404.5649) (11484.9008 5392.3053)
    ))
    ; P2596 -- see feature_dimensions_mm.csv
    ("06_ORNAMENT" 0 (
      (11556.1374 4412.2137) (11527.8321 4412.2137)
    ))
    ; P2597 -- see feature_dimensions_mm.csv
    ("06_ORNAMENT" 0 (
      (11527.8321 4412.2137) (11528.1679 4411.7252) (11528.6412 4410.0916) (11528.9618 4408.0) (11529.2824 4405.4809)
      (11529.7252 4402.6412) (11530.4427 4399.6031) (11531.4962 4396.5802) (11532.9466 4393.7405) (11534.7786 4391.2824)
      (11536.9771 4389.3893) (11539.4046 4388.1985) (11541.9847 4387.7863) (11544.5649 4388.1985) (11546.9924 4389.3893)
      (11549.1908 4391.2824) (11551.0229 4393.7405) (11552.4733 4396.5802) (11553.5267 4399.6031) (11554.2443 4402.6412)
      (11554.687 4405.4809) (11555.0076 4408.0) (11555.3282 4410.0916) (11555.8015 4411.7252) (11556.1374 4412.2137)
    ))
    ; P2598 -- see feature_dimensions_mm.csv
    ("06_ORNAMENT" 0 (
      (11540.5344 5422.5496) (11541.4198 5418.1985) (11543.9542 5410.9466) (11547.5267 5403.5725) (11552.0763 5396.2443)
      (11557.4809 5389.145) (11563.6031 5382.4427) (11570.3053 5376.3206) (11577.4046 5370.916) (11584.7328 5366.3664)
      (11592.1069 5362.7939) (11599.3588 5360.2595) (11606.2901 5358.8397) (11612.7481 5358.5802) (11618.5649 5359.4809)
      (11623.6031 5361.5115) (11627.7252 5364.6412) (11630.855 5368.7634) (11632.8855 5373.8015) (11633.7863 5379.6183)
      (11633.5267 5386.0763) (11632.1069 5393.0076) (11629.5725 5400.2595) (11626.0 5407.6336) (11621.4504 5414.9618)
      (11616.0458 5422.0611) (11609.9237 5428.7634) (11603.2214 5434.8855) (11596.1221 5440.2901) (11588.7939 5444.8397)
      (11588.5344 5444.9618)
    ))
    ; P2599 -- see feature_dimensions_mm.csv
    ("06_ORNAMENT" 0 (
      (11665.2366 4412.2137) (11556.1374 4412.2137)
    ))
    ; P2600 -- see feature_dimensions_mm.csv
    ("06_ORNAMENT" 0 (
      (11589.4809 4473.2824) (11587.9847 4478.855) (11583.8321 4483.0076) (11578.1679 4484.5191) (11572.5038 4483.0076)
      (11568.3511 4478.855) (11566.855 4473.2824)
    ))
    ; P2601 -- see feature_dimensions_mm.csv
    ("06_ORNAMENT" 0 (
      (11713.4809 4473.2824) (11722.2595 4474.4427) (11743.2824 4479.0992) (11763.8168 4485.5725) (11783.7252 4493.8168)
      (11802.8244 4503.7557) (11820.9924 4515.3282) (11838.0763 4528.4427) (11846.3969 4536.0763) (11849.4656 4537.0229)
      (11852.8244 4538.8244) (11855.7405 4541.2061) (11858.1221 4544.1221) (11859.9237 4547.4809) (11860.8702 4550.5496)
      (11868.5038 4558.8702) (11881.6183 4575.9542) (11893.1908 4594.1221) (11903.1298 4613.2214) (11911.374 4633.1298)
      (11917.8473 4653.6641) (11922.5038 4674.687) (11925.313 4696.0458) (11925.8168 4707.3282) (11927.2977 4710.1679)
      (11928.4122 4713.8168) (11928.7786 4717.5573) (11928.4122 4721.2977) (11927.2977 4724.9466) (11925.8168 4727.7863)
      (11925.313 4739.0687) (11922.5038 4760.4275) (11917.8473 4781.4504) (11911.374 4801.9847) (11903.1298 4821.8931)
      (11893.1908 4840.9924) (11881.6183 4859.1603) (11868.5038 4876.2443) (11860.8702 4884.5649) (11859.9237 4887.6336)
      (11858.1221 4890.9924) (11855.7405 4893.9084) (11852.8244 4896.2901) (11849.4656 4898.0916) (11846.3969 4899.0382)
      (11838.0763 4906.6718) (11820.9924 4919.7863) (11802.8244 4931.3588) (11783.7252 4941.2977) (11763.8168 4949.542)
      (11743.2824 4956.0153) (11722.2595 4960.6718) (11700.9008 4963.4809) (11689.6183 4963.9847) (11686.7786 4965.4656)
      (11683.1298 4966.5802) (11679.3893 4966.9466) (11675.6489 4966.5802) (11672.0 4965.4656) (11669.1603 4963.9847)
      (11657.8779 4963.4809) (11636.5191 4960.6718) (11615.4962 4956.0153) (11594.9618 4949.542) (11575.0534 4941.2977)
      (11555.9542 4931.3588) (11537.7863 4919.7863) (11520.7023 4906.6718) (11512.3817 4899.0382) (11509.313 4898.0916)
      (11505.9542 4896.2901) (11503.0382 4893.9084) (11500.6565 4890.9924) (11498.855 4887.6336) (11497.9084 4884.5649)
      (11490.2748 4876.2443) (11477.1603 4859.1603) (11465.5878 4840.9924) (11455.6489 4821.8931) (11447.4046 4801.9847)
      (11440.9313 4781.4504) (11436.2748 4760.4275) (11433.4656 4739.0687) (11432.9618 4727.7863) (11431.4809 4724.9466)
      (11430.3664 4721.2977) (11430.0 4717.5573) (11430.3664 4713.8168) (11431.4809 4710.1679) (11432.9618 4707.3282)
      (11433.4656 4696.0458) (11436.2748 4674.687) (11440.9313 4653.6641) (11447.4046 4633.1298) (11455.6489 4613.2214)
      (11465.5878 4594.1221) (11477.1603 4575.9542) (11490.2748 4558.8702) (11497.9084 4550.5496) (11498.855 4547.4809)
      (11500.6565 4544.1221) (11503.0382 4541.2061) (11505.9542 4538.8244) (11509.313 4537.0229) (11512.3817 4536.0763)
      (11520.7023 4528.4427) (11537.7863 4515.3282) (11555.9542 4503.7557) (11575.0534 4493.8168) (11594.9618 4485.5725)
      (11615.4962 4479.0992) (11636.5191 4474.4427) (11645.2977 4473.2824)
    ))
    ; P2602 -- see feature_dimensions_mm.csv
    ("06_ORNAMENT" 0 (
      (11650.0 5469.4046) (11648.2443 5461.8779) (11647.0382 5453.0382) (11646.6412 5443.9695) (11647.0382 5434.9008)
      (11648.2443 5426.0611) (11650.2137 5417.6641) (11652.9008 5409.9084) (11656.229 5403.0076) (11660.1374 5397.0992)
      (11664.5191 5392.3511) (11669.2672 5388.8702) (11674.2595 5386.7481) (11679.3893 5386.0305) (11684.5191 5386.7481)
      (11689.5115 5388.8702) (11694.2595 5392.3511) (11698.6412 5397.0992) (11702.5496 5403.0076) (11705.8779 5409.9084)
      (11708.5649 5417.6641) (11710.5344 5426.0611) (11711.7405 5434.9008) (11712.1374 5443.9695) (11711.7405 5453.0382)
      (11710.5344 5461.8779) (11708.5649 5470.2748) (11705.8779 5478.0305) (11702.5496 5484.9313) (11700.9313 5487.374)
      (11665.9847 5475.3893)
    ))
    ; P2603 -- see feature_dimensions_mm.csv
    ("06_ORNAMENT" 0 (
      (11693.542 4412.2137) (11665.2366 4412.2137)
    ))
    ; P2604 -- see feature_dimensions_mm.csv
    ("06_ORNAMENT" 0 (
      (11665.2366 4412.2137) (11665.5725 4411.7252) (11666.0458 4410.0916) (11666.3664 4408.0) (11666.5954 4406.229)
    ))
    ; P2605 -- see feature_dimensions_mm.csv
    ("06_ORNAMENT" 0 (
      (11679.3893 4528.626) (11675.6489 4528.2595) (11672.0 4527.145) (11668.5191 4525.3282) (11665.3282 4522.855)
      (11662.4733 4519.771) (11660.0305 4516.1679) (11658.0611 4512.1221) (11656.626 4507.7405) (11655.7557 4503.1298)
      (11655.4656 4498.3969) (11655.7557 4493.6641) (11656.626 4489.0534) (11658.0611 4484.6718) (11660.0305 4480.626)
      (11662.4733 4477.0229) (11665.3282 4473.9389) (11666.1679 4473.2824)
    ))
    ; P2606 -- see feature_dimensions_mm.csv
    ("06_ORNAMENT" 0 (
      (11666.5954 5001.6489) (11666.687 5000.9008) (11667.1298 4998.0611) (11667.8473 4995.0229) (11668.9008 4992.0)
      (11670.3511 4989.1603) (11670.626 4988.7786) (11669.5725 4987.7252) (11668.0611 4982.0611) (11669.5725 4976.3969)
      (11673.7252 4972.2443) (11679.3893 4970.7176) (11685.0534 4972.2443) (11689.2061 4976.3969) (11690.7328 4982.0611)
      (11689.2061 4987.7252) (11688.1527 4988.7786) (11688.4275 4989.1603) (11689.8779 4992.0) (11690.9313 4995.0229)
      (11691.6489 4998.0611) (11692.0916 5000.9008) (11692.1832 5001.6489)
    ))
    ; P2607 -- see feature_dimensions_mm.csv
    ("06_ORNAMENT" 0 (
      (11692.1832 5001.6489) (11679.3893 5002.2137) (11666.5954 5001.6489)
    ))
    ; P2608 -- see feature_dimensions_mm.csv
    ("06_ORNAMENT" 0 (
      (11666.5954 4406.229) (11666.687 4405.4809) (11667.1298 4402.6412) (11667.8473 4399.6031) (11668.9008 4396.5802)
      (11670.3511 4393.7405) (11670.626 4393.3588) (11669.5725 4392.3053) (11668.0611 4386.6412) (11669.5725 4380.9771)
      (11673.7252 4376.8244) (11679.3893 4375.2977) (11685.0534 4376.8244) (11689.2061 4380.9771) (11690.7328 4386.6412)
      (11689.2061 4392.3053) (11688.1527 4393.3588) (11688.4275 4393.7405) (11689.8779 4396.5802) (11690.9313 4399.6031)
      (11691.6489 4402.6412) (11692.0916 4405.4809) (11692.1832 4406.229)
    ))
    ; P2609 -- see feature_dimensions_mm.csv
    ("06_ORNAMENT" 0 (
      (11692.1832 4406.229) (11679.3893 4406.7939) (11666.5954 4406.229)
    ))
    ; P2610 -- see feature_dimensions_mm.csv
    ("06_ORNAMENT" 0 (
      (11692.6107 4473.2824) (11693.4504 4473.9389) (11696.3053 4477.0229) (11698.7481 4480.626) (11700.7176 4484.6718)
      (11702.1527 4489.0534) (11703.0229 4493.6641) (11703.3282 4498.3969) (11703.0229 4503.1298) (11702.1527 4507.7405)
      (11700.7176 4512.1221) (11698.7481 4516.1679) (11696.3053 4519.771) (11693.4504 4522.855) (11690.2595 4525.3282)
      (11686.7786 4527.145) (11683.1298 4528.2595) (11679.3893 4528.626)
    ))
    ; P2611 -- see feature_dimensions_mm.csv
    ("06_ORNAMENT" 1 (
      (11679.3893 4528.626) (11684.5191 4529.3435) (11689.5115 4531.4656) (11694.2595 4534.9466) (11698.6412 4539.6947)
      (11702.5496 4545.6031) (11705.8779 4552.5038) (11708.5649 4560.2595) (11710.5344 4568.6565) (11711.7405 4577.4962)
      (11712.1374 4586.5649) (11711.7405 4595.6336) (11710.5344 4604.4733) (11708.5649 4612.8702) (11705.8779 4620.626)
      (11702.5496 4627.5267) (11698.6412 4633.4351) (11694.2595 4638.1832) (11689.5115 4641.6641) (11684.5191 4643.7863)
      (11679.3893 4644.5038) (11674.2595 4643.7863) (11669.2672 4641.6641) (11664.5191 4638.1832) (11660.1374 4633.4351)
      (11656.229 4627.5267) (11652.9008 4620.626) (11650.2137 4612.8702) (11648.2443 4604.4733) (11647.0382 4595.6336)
      (11646.6412 4586.5649) (11647.0382 4577.4962) (11648.2443 4568.6565) (11650.2137 4560.2595) (11652.9008 4552.5038)
      (11656.229 4545.6031) (11660.1374 4539.6947) (11664.5191 4534.9466) (11669.2672 4531.4656) (11674.2595 4529.3435)
    ))
    ; P2612 -- see feature_dimensions_mm.csv
    ("06_ORNAMENT" 0 (
      (11962.9466 4742.4885) (11959.7252 4766.9924) (11954.3511 4791.2366) (11946.8855 4814.916) (11937.374 4837.8626)
      (11925.9084 4859.8779) (11912.5649 4880.8244) (11897.4504 4900.5344) (11880.6718 4918.8397) (11862.3664 4935.6183)
      (11842.6565 4950.7328) (11821.7252 4964.0763) (11799.6947 4975.542) (11776.7481 4985.0534) (11753.0687 4992.5191)
      (11728.8244 4997.8931) (11704.1985 5001.1298) (11692.1832 5001.6489)
    ))
    ; P2613 -- see feature_dimensions_mm.csv
    ("06_ORNAMENT" 0 (
      (11692.1832 5001.6489) (11692.4122 5003.4198) (11692.7328 5005.5115) (11693.2061 5007.145) (11693.9847 5008.3053)
      (11695.145 5009.084) (11696.7786 5009.5573) (11698.8702 5009.8779) (11701.3893 5010.1985) (11704.229 5010.6412)
      (11707.2672 5011.3588) (11710.2901 5012.4122) (11713.1298 5013.8626) (11715.5878 5015.6947) (11717.4809 5017.8931)
      (11718.6718 5020.3206) (11719.084 5022.9008) (11718.6718 5025.4809) (11717.4809 5027.9084) (11715.5878 5030.1069)
      (11714.6718 5030.7786) (11728.8244 5032.6412) (11753.0687 5038.0153) (11776.7481 5045.4809) (11799.6947 5054.9924)
      (11821.7252 5066.458) (11842.6565 5079.8015) (11862.3664 5094.916) (11880.6718 5111.6947) (11897.4504 5130.0)
      (11912.5649 5149.7099) (11925.9084 5170.6412) (11937.374 5192.6718) (11946.8855 5215.6183) (11954.3511 5239.2977)
      (11959.7252 5263.542) (11962.9618 5288.1679) (11964.0458 5312.9771) (11962.9618 5337.7863) (11959.7252 5362.4122)
      (11954.3511 5386.6565) (11946.8855 5410.3359) (11937.374 5433.2824) (11925.9084 5455.2977) (11912.5649 5476.2443)
      (11897.4504 5495.9542) (11880.6718 5514.2595) (11862.3664 5531.0382) (11860.0763 5532.7786)
    ))
    ; P2614 -- see feature_dimensions_mm.csv
    ("06_ORNAMENT" 0 (
      (11963.4962 4134.5802) (11962.9618 4146.9466) (11959.7252 4171.5725) (11954.3511 4195.8168) (11946.8855 4219.4962)
      (11937.374 4242.4427) (11925.9084 4264.458) (11912.5649 4285.4046) (11897.4504 4305.1145) (11880.6718 4323.4198)
      (11862.3664 4340.1985) (11842.6565 4355.313) (11821.7252 4368.6565) (11799.6947 4380.1221) (11776.7481 4389.6336)
      (11753.0687 4397.0992) (11728.8244 4402.4733) (11704.1985 4405.7099) (11692.1832 4406.229)
    ))
    ; P2615 -- see feature_dimensions_mm.csv
    ("06_ORNAMENT" 0 (
      (11692.1832 4406.229) (11692.4122 4408.0) (11692.7328 4410.0916) (11693.2061 4411.7252) (11693.542 4412.2137)
    ))
    ; P2616 -- see feature_dimensions_mm.csv
    ("06_ORNAMENT" 0 (
      (11802.6412 4412.2137) (11693.542 4412.2137)
    ))
    ; P2617 -- see feature_dimensions_mm.csv
    ("06_ORNAMENT" 0 (
      (11745.7405 5501.6641) (11737.2672 5498.9924) (11739.9847 5493.6641) (11745.5573 5488.0916) (11752.5802 5484.5191)
      (11760.3664 5483.2824) (11768.1527 5484.5191) (11775.1756 5488.0916) (11780.7481 5493.6641) (11784.3206 5500.687)
      (11785.5573 5508.4733) (11784.8244 5513.084)
    ))
    ; P2618 -- see feature_dimensions_mm.csv
    ("06_ORNAMENT" 0 (
      (11791.9237 4473.2824) (11790.4275 4478.855) (11786.2748 4483.0076) (11780.6107 4484.5191) (11774.9466 4483.0076)
      (11770.7939 4478.855) (11769.2977 4473.2824)
    ))
    ; P2619 -- see feature_dimensions_mm.csv
    ("06_ORNAMENT" 0 (
      (11830.9466 4412.2137) (11802.6412 4412.2137)
    ))
    ; P2620 -- see feature_dimensions_mm.csv
    ("06_ORNAMENT" 0 (
      (11802.6412 4412.2137) (11802.9771 4411.7252) (11803.4504 4410.0916) (11803.771 4408.0) (11804.0916 4405.4809)
      (11804.5344 4402.6412) (11805.2519 4399.6031) (11806.3053 4396.5802) (11807.7557 4393.7405) (11809.5878 4391.2824)
      (11811.7863 4389.3893) (11814.2137 4388.1985) (11816.7939 4387.7863) (11819.374 4388.1985) (11821.8015 4389.3893)
      (11824.0 4391.2824) (11825.8321 4393.7405) (11827.2824 4396.5802) (11828.3359 4399.6031) (11829.0534 4402.6412)
      (11829.4962 4405.4809) (11829.8168 4408.0) (11830.1374 4410.0916) (11830.6107 4411.7252) (11830.9466 4412.2137)
    ))
    ; P2621 -- see feature_dimensions_mm.csv
    ("06_ORNAMENT" 0 (
      (11808.0 1928.2748) (11801.3588 1955.0229) (11797.0687 1956.9771) (11786.6565 1959.7557) (11775.2519 1961.0992)
      (11763.145 1960.9618) (11750.6412 1959.3435) (11738.0305 1956.3053) (11725.6336 1951.9084) (11713.7557 1946.2595)
      (11702.687 1939.4962) (11692.7023 1931.7863) (11684.0458 1923.313) (11676.9313 1914.3053) (11671.542 1904.9771)
      (11668.0 1895.542) (11666.3817 1886.2595) (11666.7481 1877.3282) (11669.084 1868.9924) (11673.3282 1861.4504)
      (11679.3893 1854.8702) (11687.0992 1849.4351) (11696.2748 1845.2824) (11706.687 1842.5038) (11718.0916 1841.1603)
      (11730.1832 1841.2977) (11742.7023 1842.9008) (11755.2977 1845.9542) (11767.6947 1850.3511) (11779.5725 1856.0)
      (11790.6412 1862.7634) (11800.626 1870.4733) (11809.2824 1878.9313) (11814.4427 1885.4809) (11812.8702 1900.4733)
    ))
    ; P2622 -- see feature_dimensions_mm.csv
    ("06_ORNAMENT" 0 (
      (11825.2366 4473.2824) (11842.6565 4484.3817) (11862.3664 4499.4962) (11880.6718 4516.2748) (11897.4504 4534.5802)
      (11912.5649 4554.2901) (11925.9084 4575.2214) (11937.374 4597.2519) (11946.8855 4620.1985) (11954.3511 4643.8779)
      (11959.7252 4668.1221) (11962.9618 4692.7481) (11964.0458 4717.5573) (11963.1603 4737.8931)
    ))
    ; P2623 -- see feature_dimensions_mm.csv
    ("06_ORNAMENT" 0 (
      (12022.9008 4412.2137) (11830.9466 4412.2137)
    ))
    ; P2624 -- see feature_dimensions_mm.csv
    ("06_ORNAMENT" 0 (
      (11963.1603 4737.8931) (11962.9618 4742.3664) (11962.9466 4742.4885)
    ))
    ; P2625 -- see feature_dimensions_mm.csv
    ("06_ORNAMENT" 0 (
      (11962.9466 4742.4885) (11962.5954 4740.7176) (11963.1603 4737.8931)
    ))
    ; P2626 -- see feature_dimensions_mm.csv
    ("06_ORNAMENT" 0 (
      (11963.1603 4737.8931) (11963.8168 4734.5802) (11967.2977 4729.374) (11972.4885 4725.9084) (11978.626 4724.687)
      (11984.7634 4725.9084) (11989.9542 4729.374) (11993.4351 4734.5802) (11994.6565 4740.7176) (11993.4351 4746.855)
      (11989.9542 4752.0458) (11984.7634 4755.5267) (11978.626 4756.7481) (11972.4885 4755.5267) (11967.2977 4752.0458)
      (11963.8168 4746.855) (11962.9466 4742.4885)
    ))
    ; P2627 -- see feature_dimensions_mm.csv
    ("06_ORNAMENT" 0 (
      (11963.9847 4123.6489) (11963.4962 4134.5802)
    ))
    ; P2628 -- see feature_dimensions_mm.csv
    ("06_ORNAMENT" 0 (
      (11963.4962 4134.5802) (11962.5954 4130.0305) (11963.8168 4123.8931) (11963.9847 4123.6489)
    ))
    ; P2629 -- see feature_dimensions_mm.csv
    ("06_ORNAMENT" 0 (
      (11963.9847 4123.6489) (11967.2977 4118.687) (11972.4885 4115.2214) (11978.626 4114.0) (11984.7634 4115.2214)
      (11989.9542 4118.687) (11993.4351 4123.8931) (11994.6565 4130.0305) (11993.4351 4136.1679) (11989.9542 4141.3588)
      (11984.7634 4144.8397) (11978.626 4146.0611) (11972.4885 4144.8397) (11967.2977 4141.3588) (11963.8168 4136.1679)
      (11963.4962 4134.5802)
    ))
    ; P2630 -- see feature_dimensions_mm.csv
    ("06_ORNAMENT" 0 (
      (12099.2366 4412.2137) (12076.3359 4412.2137) (12076.3359 3832.0611)
    ))
    ; P2631 -- see feature_dimensions_mm.csv
    ("06_ORNAMENT" 0 (
      (12167.0076 5938.9313) (12186.6565 5940.3206) (12211.4351 5943.7863) (12236.8855 5948.8397) (12262.7176 5955.313)
      (12288.5649 5962.9924) (12314.1374 5971.7099) (12339.1145 5981.2672) (12363.145 5991.4809) (12385.9237 6002.1679)
      (12407.1145 6013.1298) (12426.4122 6024.1832) (12443.4962 6035.1298) (12458.0153 6045.8015) (12438.1374 6044.9008)
      (12416.4427 6042.7939) (12393.2519 6039.5573) (12368.9313 6035.1908) (12343.8168 6029.7557) (12318.2901 6023.2977)
      (12292.6718 6015.8321) (12267.313 6007.4046) (12242.5802 5998.0611) (12218.8244 5987.8473) (12196.3817 5976.7786)
      (12175.6031 5964.916) (12156.8397 5952.2901) (12140.458 5938.9313)
    ))
    ; P2632 -- see feature_dimensions_mm.csv
    ("06_ORNAMENT" 0 (
      (12158.1527 4123.6489) (12158.0916 4122.1374) (12159.1756 4097.3282) (12162.4122 4072.7023) (12167.7863 4048.458)
      (12175.2519 4024.7786) (12184.7634 4001.8321) (12196.229 3979.8015) (12209.5725 3958.8702) (12224.687 3939.1603)
      (12241.4656 3920.855) (12259.771 3904.0763) (12279.4809 3888.9618) (12300.4275 3875.6183) (12322.4427 3864.1527)
      (12345.3893 3854.6412) (12369.0687 3847.1756) (12393.313 3841.8015) (12417.9389 3838.5649) (12442.7481 3837.4809)
      (12467.5573 3838.5649) (12492.1832 3841.8015) (12516.4275 3847.1756) (12540.1069 3854.6412) (12563.0534 3864.1527)
      (12585.084 3875.6183) (12606.0153 3888.9618) (12625.7252 3904.0763) (12644.0305 3920.855) (12660.8092 3939.1603)
      (12675.9237 3958.8702) (12689.2672 3979.8015) (12700.7328 4001.8321) (12710.2443 4024.7786) (12717.7099 4048.458)
      (12723.084 4072.7023) (12726.3206 4097.3282) (12727.4046 4122.1374) (12727.3435 4123.6489)
    ))
    ; P2633 -- see feature_dimensions_mm.csv
    ("06_ORNAMENT" 0 (
      (12158.6412 4134.5802) (12158.3206 4136.1679) (12154.8397 4141.3588) (12149.6489 4144.8397) (12143.5115 4146.0611)
      (12137.374 4144.8397) (12132.1832 4141.3588) (12128.7023 4136.1679) (12127.4809 4130.0305) (12128.7023 4123.8931)
      (12132.1832 4118.687) (12137.374 4115.2214) (12143.5115 4114.0) (12149.6489 4115.2214) (12154.8397 4118.687)
      (12158.1527 4123.6489)
    ))
    ; P2634 -- see feature_dimensions_mm.csv
    ("06_ORNAMENT" 0 (
      (12158.6412 4134.5802) (12158.1527 4123.6489)
    ))
    ; P2635 -- see feature_dimensions_mm.csv
    ("06_ORNAMENT" 0 (
      (12158.1527 4123.6489) (12158.3206 4123.8931) (12159.542 4130.0305) (12158.6412 4134.5802)
    ))
    ; P2636 -- see feature_dimensions_mm.csv
    ("06_ORNAMENT" 0 (
      (12429.9542 4406.229) (12417.9389 4405.7099) (12393.313 4402.4733) (12369.0687 4397.0992) (12345.3893 4389.6336)
      (12322.4427 4380.1221) (12300.4275 4368.6565) (12279.4809 4355.313) (12259.771 4340.1985) (12241.4656 4323.4198)
      (12224.687 4305.1145) (12209.5725 4285.4046) (12196.229 4264.458) (12184.7634 4242.4427) (12175.2519 4219.4962)
      (12167.7863 4195.8168) (12162.4122 4171.5725) (12159.1756 4146.9466) (12158.6412 4134.5802)
    ))
    ; P2637 -- see feature_dimensions_mm.csv
    ("06_ORNAMENT" 0 (
      (12158.9771 4737.8931) (12158.0916 4717.5573) (12159.1756 4692.7481) (12162.4122 4668.1221) (12167.7863 4643.8779)
      (12175.2519 4620.1985) (12184.7634 4597.2519) (12196.229 4575.2214) (12209.5725 4554.2901) (12224.687 4534.5802)
      (12241.4656 4516.2748) (12259.771 4499.4962) (12279.4809 4484.3817) (12296.9008 4473.2824)
    ))
    ; P2638 -- see feature_dimensions_mm.csv
    ("06_ORNAMENT" 0 (
      (12159.1908 4742.4885) (12158.3206 4746.855) (12154.8397 4752.0458) (12149.6489 4755.5267) (12143.5115 4756.7481)
      (12137.374 4755.5267) (12132.1832 4752.0458) (12128.7023 4746.855) (12127.4809 4740.7176) (12128.7023 4734.5802)
      (12132.1832 4729.374) (12137.374 4725.9084) (12143.5115 4724.687) (12149.6489 4725.9084) (12154.8397 4729.374)
      (12158.3206 4734.5802) (12158.9771 4737.8931)
    ))
    ; P2639 -- see feature_dimensions_mm.csv
    ("06_ORNAMENT" 0 (
      (12159.1908 4742.4885) (12159.1756 4742.3664) (12158.9771 4737.8931)
    ))
    ; P2640 -- see feature_dimensions_mm.csv
    ("06_ORNAMENT" 0 (
      (12158.9771 4737.8931) (12159.542 4740.7176) (12159.1908 4742.4885)
    ))
    ; P2641 -- see feature_dimensions_mm.csv
    ("06_ORNAMENT" 0 (
      (12429.9542 5001.6489) (12417.9389 5001.1298) (12393.313 4997.8931) (12369.0687 4992.5191) (12345.3893 4985.0534)
      (12322.4427 4975.542) (12300.4275 4964.0763) (12279.4809 4950.7328) (12259.771 4935.6183) (12241.4656 4918.8397)
      (12224.687 4900.5344) (12209.5725 4880.8244) (12196.229 4859.8779) (12184.7634 4837.8626) (12175.2519 4814.916)
      (12167.7863 4791.2366) (12162.4122 4766.9924) (12159.1908 4742.4885)
    ))
    ; P2642 -- see feature_dimensions_mm.csv
    ("06_ORNAMENT" 0 (
      (12262.0611 5532.7786) (12259.771 5531.0382) (12241.4656 5514.2595) (12224.687 5495.9542) (12209.5725 5476.2443)
      (12196.229 5455.2977) (12184.7634 5433.2824) (12175.2519 5410.3359) (12167.7863 5386.6565) (12162.4122 5362.4122)
      (12159.1756 5337.7863) (12158.0916 5312.9771) (12159.1756 5288.1679) (12162.4122 5263.542) (12167.7863 5239.2977)
      (12175.2519 5215.6183) (12184.7634 5192.6718) (12196.229 5170.6412) (12209.5725 5149.7099) (12224.687 5130.0)
      (12241.4656 5111.6947) (12259.771 5094.916) (12279.4809 5079.8015) (12300.4275 5066.458) (12322.4427 5054.9924)
      (12345.3893 5045.4809) (12369.0687 5038.0153) (12393.313 5032.6412) (12407.4656 5030.7786) (12406.5496 5030.1069)
      (12404.6565 5027.9084) (12403.4656 5025.4809) (12403.0534 5022.9008) (12403.4656 5020.3206) (12404.6565 5017.8931)
      (12406.5496 5015.6947) (12409.0076 5013.8626) (12411.8473 5012.4122) (12414.8702 5011.3588) (12417.9084 5010.6412)
      (12420.7481 5010.1985) (12423.2672 5009.8779) (12425.3588 5009.5573) (12426.9924 5009.084) (12428.1527 5008.3053)
      (12428.9313 5007.145) (12429.4046 5005.5115) (12429.7252 5003.4198) (12429.9542 5001.6489)
    ))
    ; P2643 -- see feature_dimensions_mm.csv
    ("06_ORNAMENT" 0 (
      (12291.1908 4412.2137) (12291.5267 4411.7252) (12292.0 4410.0916) (12292.3206 4408.0) (12292.6412 4405.4809)
      (12293.084 4402.6412) (12293.8015 4399.6031) (12294.855 4396.5802) (12296.3053 4393.7405) (12298.1374 4391.2824)
      (12300.3359 4389.3893) (12302.7634 4388.1985) (12305.3435 4387.7863) (12307.9237 4388.1985) (12310.3511 4389.3893)
      (12312.5496 4391.2824) (12314.3817 4393.7405) (12315.8321 4396.5802) (12316.8855 4399.6031) (12317.6031 4402.6412)
      (12318.0458 4405.4809) (12318.3664 4408.0) (12318.687 4410.0916) (12319.1603 4411.7252) (12319.4962 4412.2137)
    ))
    ; P2644 -- see feature_dimensions_mm.csv
    ("06_ORNAMENT" 0 (
      (12309.6183 5520.5954) (12301.145 5515.2061) (12284.0611 5502.0916) (12275.7405 5494.458) (12272.6718 5493.5115)
      (12269.313 5491.7099) (12266.3969 5489.3282) (12264.0153 5486.4122) (12262.2137 5483.0534) (12261.2672 5479.9847)
      (12253.6336 5471.6641) (12240.5191 5454.5802) (12228.9466 5436.4122) (12219.0076 5417.313) (12210.7634 5397.4046)
      (12204.2901 5376.8702) (12199.6336 5355.8473) (12196.8244 5334.4885) (12196.3206 5323.2061) (12194.8397 5320.3664)
      (12193.7252 5316.7176) (12193.3588 5312.9771) (12193.7252 5309.2366) (12194.8397 5305.5878) (12196.3206 5302.7481)
      (12196.8244 5291.4656) (12199.6336 5270.1069) (12204.2901 5249.084) (12210.7634 5228.5496) (12219.0076 5208.6412)
      (12228.9466 5189.542) (12240.5191 5171.374) (12253.6336 5154.2901) (12261.2672 5145.9695) (12262.2137 5142.9008)
      (12264.0153 5139.542) (12266.3969 5136.626) (12269.313 5134.2443) (12272.6718 5132.4427) (12275.7405 5131.4962)
      (12284.0611 5123.8626) (12301.145 5110.7481) (12319.313 5099.1756) (12338.4122 5089.2366) (12358.3206 5080.9924)
      (12378.855 5074.5191) (12399.8779 5069.8626) (12421.2366 5067.0534) (12432.5191 5066.5496) (12435.3588 5065.0687)
      (12439.0076 5063.9542) (12442.7481 5063.5878) (12446.4885 5063.9542) (12450.1374 5065.0687) (12452.9771 5066.5496)
      (12464.2595 5067.0534) (12485.6183 5069.8626) (12506.6412 5074.5191) (12527.1756 5080.9924) (12547.084 5089.2366)
      (12566.1832 5099.1756) (12584.3511 5110.7481) (12601.4351 5123.8626) (12609.7557 5131.4962) (12612.8244 5132.4427)
      (12616.1832 5134.2443) (12619.0992 5136.626) (12621.4809 5139.542) (12623.2824 5142.9008) (12624.229 5145.9695)
      (12631.8626 5154.2901) (12644.9771 5171.374) (12656.5496 5189.542) (12666.4885 5208.6412) (12674.7328 5228.5496)
      (12681.2061 5249.084) (12685.8626 5270.1069) (12688.6718 5291.4656) (12689.1756 5302.7481) (12690.6565 5305.5878)
      (12691.771 5309.2366) (12692.1374 5312.9771) (12691.771 5316.7176) (12690.6565 5320.3664) (12689.1756 5323.2061)
      (12688.6718 5334.4885) (12685.8626 5355.8473) (12685.0992 5359.2824) (12667.4351 5372.6565)
    ))
    ; P2645 -- see feature_dimensions_mm.csv
    ("06_ORNAMENT" 0 (
      (12352.8397 4473.2824) (12351.3435 4478.855) (12347.1908 4483.0076) (12341.5267 4484.5191) (12335.8626 4483.0076)
      (12331.7099 4478.855) (12330.2137 4473.2824)
    ))
    ; P2646 -- see feature_dimensions_mm.csv
    ("06_ORNAMENT" 0 (
      (12337.313 5513.084) (12336.5802 5508.4733) (12337.8168 5500.687) (12341.3893 5493.6641) (12346.9618 5488.0916)
      (12353.9847 5484.5191) (12361.771 5483.2824) (12369.5573 5484.5191) (12376.5802 5488.0916) (12382.1527 5493.6641)
      (12384.8702 5498.9924) (12376.3969 5501.6641)
    ))
    ; P2647 -- see feature_dimensions_mm.csv
    ("06_ORNAMENT" 0 (
      (12476.8397 4473.2824) (12485.6183 4474.4427) (12506.6412 4479.0992) (12527.1756 4485.5725) (12547.084 4493.8168)
      (12566.1832 4503.7557) (12584.3511 4515.3282) (12601.4351 4528.4427) (12609.7557 4536.0763) (12612.8244 4537.0229)
      (12616.1832 4538.8244) (12619.0992 4541.2061) (12621.4809 4544.1221) (12623.2824 4547.4809) (12624.229 4550.5496)
      (12631.8626 4558.8702) (12644.9771 4575.9542) (12656.5496 4594.1221) (12666.4885 4613.2214) (12674.7328 4633.1298)
      (12681.2061 4653.6641) (12685.8626 4674.687) (12688.6718 4696.0458) (12689.1756 4707.3282) (12690.6565 4710.1679)
      (12691.771 4713.8168) (12692.1374 4717.5573) (12691.771 4721.2977) (12690.6565 4724.9466) (12689.1756 4727.7863)
      (12688.6718 4739.0687) (12685.8626 4760.4275) (12681.2061 4781.4504) (12674.7328 4801.9847) (12666.4885 4821.8931)
      (12656.5496 4840.9924) (12644.9771 4859.1603) (12631.8626 4876.2443) (12624.229 4884.5649) (12623.2824 4887.6336)
      (12621.4809 4890.9924) (12619.0992 4893.9084) (12616.1832 4896.2901) (12612.8244 4898.0916) (12609.7557 4899.0382)
      (12601.4351 4906.6718) (12584.3511 4919.7863) (12566.1832 4931.3588) (12547.084 4941.2977) (12527.1756 4949.542)
      (12506.6412 4956.0153) (12485.6183 4960.6718) (12464.2595 4963.4809) (12452.9771 4963.9847) (12450.1374 4965.4656)
      (12446.4885 4966.5802) (12442.7481 4966.9466) (12439.0076 4966.5802) (12435.3588 4965.4656) (12432.5191 4963.9847)
      (12421.2366 4963.4809) (12399.8779 4960.6718) (12378.855 4956.0153) (12358.3206 4949.542) (12338.4122 4941.2977)
      (12319.313 4931.3588) (12301.145 4919.7863) (12284.0611 4906.6718) (12275.7405 4899.0382) (12272.6718 4898.0916)
      (12269.313 4896.2901) (12266.3969 4893.9084) (12264.0153 4890.9924) (12262.2137 4887.6336) (12261.2672 4884.5649)
      (12253.6336 4876.2443) (12240.5191 4859.1603) (12228.9466 4840.9924) (12219.0076 4821.8931) (12210.7634 4801.9847)
      (12204.2901 4781.4504) (12199.6336 4760.4275) (12196.8244 4739.0687) (12196.3206 4727.7863) (12194.8397 4724.9466)
      (12193.7252 4721.2977) (12193.3588 4717.5573) (12193.7252 4713.8168) (12194.8397 4710.1679) (12196.3206 4707.3282)
      (12196.8244 4696.0458) (12199.6336 4674.687) (12204.2901 4653.6641) (12210.7634 4633.1298) (12219.0076 4613.2214)
      (12228.9466 4594.1221) (12240.5191 4575.9542) (12253.6336 4558.8702) (12261.2672 4550.5496) (12262.2137 4547.4809)
      (12264.0153 4544.1221) (12266.3969 4541.2061) (12269.313 4538.8244) (12272.6718 4537.0229) (12275.7405 4536.0763)
      (12284.0611 4528.4427) (12301.145 4515.3282) (12319.313 4503.7557) (12338.4122 4493.8168) (12358.3206 4485.5725)
      (12378.855 4479.0992) (12399.8779 4474.4427) (12408.6565 4473.2824)
    ))
    ; P2648 -- see feature_dimensions_mm.csv
    ("06_ORNAMENT" 0 (
      (12428.5954 4412.2137) (12428.9313 4411.7252) (12429.4046 4410.0916) (12429.7252 4408.0) (12429.9542 4406.229)
    ))
    ; P2649 -- see feature_dimensions_mm.csv
    ("06_ORNAMENT" 0 (
      (12442.7481 4528.626) (12439.0076 4528.2595) (12435.3588 4527.145) (12431.8779 4525.3282) (12428.687 4522.855)
      (12425.8321 4519.771) (12423.3893 4516.1679) (12421.4198 4512.1221) (12419.9847 4507.7405) (12419.1145 4503.1298)
      (12418.8244 4498.3969) (12419.1145 4493.6641) (12419.9847 4489.0534) (12421.4198 4484.6718) (12423.3893 4480.626)
      (12425.8321 4477.0229) (12428.687 4473.9389) (12429.5267 4473.2824)
    ))
    ; P2650 -- see feature_dimensions_mm.csv
    ("06_ORNAMENT" 0 (
      (12429.9542 5001.6489) (12430.0458 5000.9008) (12430.4885 4998.0611) (12431.2061 4995.0229) (12432.2595 4992.0)
      (12433.7099 4989.1603) (12433.9847 4988.7786) (12432.9313 4987.7252) (12431.4198 4982.0611) (12432.9313 4976.3969)
      (12437.084 4972.2443) (12442.7481 4970.7176) (12448.4122 4972.2443) (12452.5649 4976.3969) (12454.0916 4982.0611)
      (12452.5649 4987.7252) (12451.5115 4988.7786) (12451.7863 4989.1603) (12453.2366 4992.0) (12454.2901 4995.0229)
      (12455.0076 4998.0611) (12455.4504 5000.9008) (12455.542 5001.6489)
    ))
    ; P2651 -- see feature_dimensions_mm.csv
    ("06_ORNAMENT" 0 (
      (12455.542 5001.6489) (12442.7481 5002.2137) (12429.9542 5001.6489)
    ))
    ; P2652 -- see feature_dimensions_mm.csv
    ("06_ORNAMENT" 0 (
      (12429.9542 4406.229) (12430.0458 4405.4809) (12430.4885 4402.6412) (12431.2061 4399.6031) (12432.2595 4396.5802)
      (12433.7099 4393.7405) (12433.9847 4393.3588) (12432.9313 4392.3053) (12431.4198 4386.6412) (12432.9313 4380.9771)
      (12437.084 4376.8244) (12442.7481 4375.2977) (12448.4122 4376.8244) (12452.5649 4380.9771) (12454.0916 4386.6412)
      (12452.5649 4392.3053) (12451.5115 4393.3588) (12451.7863 4393.7405) (12453.2366 4396.5802) (12454.2901 4399.6031)
      (12455.0076 4402.6412) (12455.4504 4405.4809) (12455.542 4406.229)
    ))
    ; P2653 -- see feature_dimensions_mm.csv
    ("06_ORNAMENT" 0 (
      (12455.542 4406.229) (12442.7481 4406.7939) (12429.9542 4406.229)
    ))
    ; P2654 -- see feature_dimensions_mm.csv
    ("06_ORNAMENT" 0 (
      (12455.9695 4473.2824) (12456.8092 4473.9389) (12459.6641 4477.0229) (12462.1069 4480.626) (12464.0763 4484.6718)
      (12465.5115 4489.0534) (12466.3817 4493.6641) (12466.687 4498.3969) (12466.3817 4503.1298) (12465.5115 4507.7405)
      (12464.0763 4512.1221) (12462.1069 4516.1679) (12459.6641 4519.771) (12456.8092 4522.855) (12453.6183 4525.3282)
      (12450.1374 4527.145) (12446.4885 4528.2595) (12442.7481 4528.626)
    ))
    ; P2655 -- see feature_dimensions_mm.csv
    ("06_ORNAMENT" 1 (
      (12442.7481 4528.626) (12447.8779 4529.3435) (12452.8702 4531.4656) (12457.6183 4534.9466) (12462.0 4539.6947)
      (12465.9084 4545.6031) (12469.2366 4552.5038) (12471.9237 4560.2595) (12473.8931 4568.6565) (12475.0992 4577.4962)
      (12475.4962 4586.5649) (12475.0992 4595.6336) (12473.8931 4604.4733) (12471.9237 4612.8702) (12469.2366 4620.626)
      (12465.9084 4627.5267) (12462.0 4633.4351) (12457.6183 4638.1832) (12452.8702 4641.6641) (12447.8779 4643.7863)
      (12442.7481 4644.5038) (12437.6183 4643.7863) (12432.626 4641.6641) (12427.8779 4638.1832) (12423.4962 4633.4351)
      (12419.5878 4627.5267) (12416.2595 4620.626) (12413.5725 4612.8702) (12411.6031 4604.4733) (12410.3969 4595.6336)
      (12410.0 4586.5649) (12410.3969 4577.4962) (12411.6031 4568.6565) (12413.5725 4560.2595) (12416.2595 4552.5038)
      (12419.5878 4545.6031) (12423.4962 4539.6947) (12427.8779 4534.9466) (12432.626 4531.4656) (12437.6183 4529.3435)
    ))
    ; P2656 -- see feature_dimensions_mm.csv
    ("06_ORNAMENT" 0 (
      (12726.3053 4742.4885) (12723.084 4766.9924) (12717.7099 4791.2366) (12710.2443 4814.916) (12700.7328 4837.8626)
      (12689.2672 4859.8779) (12675.9237 4880.8244) (12660.8092 4900.5344) (12644.0305 4918.8397) (12625.7252 4935.6183)
      (12606.0153 4950.7328) (12585.084 4964.0763) (12563.0534 4975.542) (12540.1069 4985.0534) (12516.4275 4992.5191)
      (12492.1832 4997.8931) (12467.5573 5001.1298) (12455.542 5001.6489)
    ))
    ; P2657 -- see feature_dimensions_mm.csv
    ("06_ORNAMENT" 0 (
      (12455.542 5001.6489) (12455.771 5003.4198) (12456.0916 5005.5115) (12456.5649 5007.145) (12457.3435 5008.3053)
      (12458.5038 5009.084) (12460.1374 5009.5573) (12462.229 5009.8779) (12464.7481 5010.1985) (12467.5878 5010.6412)
      (12470.626 5011.3588) (12473.6489 5012.4122) (12476.4885 5013.8626) (12478.9466 5015.6947) (12480.8397 5017.8931)
      (12482.0305 5020.3206) (12482.4427 5022.9008) (12482.0305 5025.4809) (12480.8397 5027.9084) (12478.9466 5030.1069)
      (12478.0305 5030.7786) (12492.1832 5032.6412) (12516.4275 5038.0153) (12540.1069 5045.4809) (12563.0534 5054.9924)
      (12585.084 5066.458) (12606.0153 5079.8015) (12625.7252 5094.916) (12644.0305 5111.6947) (12660.8092 5130.0)
      (12675.9237 5149.7099) (12689.2672 5170.6412) (12700.7328 5192.6718) (12710.2443 5215.6183) (12717.7099 5239.2977)
      (12723.084 5263.542) (12726.3206 5288.1679) (12727.4046 5312.9771) (12727.0382 5321.2519) (12718.8855 5330.2901)
    ))
    ; P2658 -- see feature_dimensions_mm.csv
    ("06_ORNAMENT" 0 (
      (12726.855 4134.5802) (12726.3206 4146.9466) (12723.084 4171.5725) (12717.7099 4195.8168) (12710.2443 4219.4962)
      (12700.7328 4242.4427) (12689.2672 4264.458) (12675.9237 4285.4046) (12660.8092 4305.1145) (12644.0305 4323.4198)
      (12625.7252 4340.1985) (12606.0153 4355.313) (12585.084 4368.6565) (12563.0534 4380.1221) (12540.1069 4389.6336)
      (12516.4275 4397.0992) (12492.1832 4402.4733) (12467.5573 4405.7099) (12455.542 4406.229)
    ))
    ; P2659 -- see feature_dimensions_mm.csv
    ("06_ORNAMENT" 0 (
      (12455.542 4406.229) (12455.771 4408.0) (12456.0916 4410.0916) (12456.5649 4411.7252) (12456.9008 4412.2137)
    ))
    ; P2660 -- see feature_dimensions_mm.csv
    ("06_ORNAMENT" 0 (
      (12456.1527 5475.3893) (12421.2061 5487.374) (12419.5878 5484.9313) (12416.2595 5478.0305) (12413.5725 5470.2748)
      (12411.6031 5461.8779) (12410.3969 5453.0382) (12410.0 5443.9695) (12410.3969 5434.9008) (12411.6031 5426.0611)
      (12413.5725 5417.6641) (12416.2595 5409.9084) (12419.5878 5403.0076) (12423.4962 5397.0992) (12427.8779 5392.3511)
      (12432.626 5388.8702) (12437.6183 5386.7481) (12442.7481 5386.0305) (12447.8779 5386.7481) (12452.8702 5388.8702)
      (12457.6183 5392.3511) (12462.0 5397.0992) (12465.9084 5403.0076) (12469.2366 5409.9084) (12471.9237 5417.6641)
      (12473.8931 5426.0611) (12475.0992 5434.9008) (12475.4962 5443.9695) (12475.0992 5453.0382) (12473.8931 5461.8779)
      (12472.1374 5469.4046)
    ))
    ; P2661 -- see feature_dimensions_mm.csv
    ("06_ORNAMENT" 0 (
      (12555.2824 4473.2824) (12553.7863 4478.855) (12549.6336 4483.0076) (12543.9695 4484.5191) (12538.3053 4483.0076)
      (12534.1527 4478.855) (12532.6565 4473.2824)
    ))
    ; P2662 -- see feature_dimensions_mm.csv
    ("06_ORNAMENT" 0 (
      (12533.6031 5444.9618) (12533.3435 5444.8397) (12526.0153 5440.2901) (12518.916 5434.8855) (12512.2137 5428.7634)
      (12506.0916 5422.0611) (12500.687 5414.9618) (12496.1374 5407.6336) (12492.5649 5400.2595) (12490.0305 5393.0076)
      (12488.6107 5386.0763) (12488.3511 5379.6183) (12489.2519 5373.8015) (12491.2824 5368.7634) (12494.4122 5364.6412)
      (12498.5344 5361.5115) (12503.5725 5359.4809) (12509.3893 5358.5802) (12515.8473 5358.8397) (12522.7786 5360.2595)
      (12530.0305 5362.7939) (12537.4046 5366.3664) (12544.7328 5370.916) (12551.8321 5376.3206) (12558.5344 5382.4427)
      (12564.6565 5389.145) (12570.0611 5396.2443) (12574.6107 5403.5725) (12578.1832 5410.9466) (12580.7176 5418.1985)
      (12581.6031 5422.5496)
    ))
    ; P2663 -- see feature_dimensions_mm.csv
    ("06_ORNAMENT" 0 (
      (12566.0 4412.2137) (12566.3359 4411.7252) (12566.8092 4410.0916) (12567.1298 4408.0) (12567.4504 4405.4809)
      (12567.8931 4402.6412) (12568.6107 4399.6031) (12569.6641 4396.5802) (12571.1145 4393.7405) (12572.9466 4391.2824)
      (12575.145 4389.3893) (12577.5725 4388.1985) (12580.1527 4387.7863) (12582.7328 4388.1985) (12585.1603 4389.3893)
      (12587.3588 4391.2824) (12589.1908 4393.7405) (12590.6412 4396.5802) (12591.6947 4399.6031) (12592.4122 4402.6412)
      (12592.855 4405.4809) (12593.1756 4408.0) (12593.4962 4410.0916) (12593.9695 4411.7252) (12594.3053 4412.2137)
    ))
    ; P2664 -- see feature_dimensions_mm.csv
    ("06_ORNAMENT" 0 (
      (12588.5954 4473.2824) (12606.0153 4484.3817) (12625.7252 4499.4962) (12644.0305 4516.2748) (12660.8092 4534.5802)
      (12675.9237 4554.2901) (12689.2672 4575.2214) (12700.7328 4597.2519) (12710.2443 4620.1985) (12717.7099 4643.8779)
      (12723.084 4668.1221) (12726.3206 4692.7481) (12727.4046 4717.5573) (12726.5191 4737.8931)
    ))
    ; P2665 -- see feature_dimensions_mm.csv
    ("06_ORNAMENT" 0 (
      (12637.2366 5392.3053) (12615.7252 5404.5649) (12614.2901 5401.7405) (12613.0534 5393.9542) (12614.2901 5386.1679)
      (12617.8626 5379.145) (12623.4351 5373.5725) (12630.458 5370.0) (12638.2443 5368.7634) (12646.0305 5370.0)
      (12653.0534 5373.5725) (12658.1679 5378.687)
    ))
    ; P2666 -- see feature_dimensions_mm.csv
    ("06_ORNAMENT" 0 (
      (12726.5191 4737.8931) (12726.3206 4742.3664) (12726.3053 4742.4885)
    ))
    ; P2667 -- see feature_dimensions_mm.csv
    ("06_ORNAMENT" 0 (
      (12726.3053 4742.4885) (12725.9542 4740.7176) (12726.5191 4737.8931)
    ))
    ; P2668 -- see feature_dimensions_mm.csv
    ("06_ORNAMENT" 0 (
      (12726.5191 4737.8931) (12727.1756 4734.5802) (12730.6565 4729.374) (12735.8473 4725.9084) (12741.9847 4724.687)
      (12748.1221 4725.9084) (12753.313 4729.374) (12756.7939 4734.5802) (12758.0153 4740.7176) (12756.7939 4746.855)
      (12753.313 4752.0458) (12748.1221 4755.5267) (12741.9847 4756.7481) (12735.8473 4755.5267) (12730.6565 4752.0458)
      (12727.1756 4746.855) (12726.3053 4742.4885)
    ))
    ; P2669 -- see feature_dimensions_mm.csv
    ("06_ORNAMENT" 0 (
      (12727.3435 4123.6489) (12726.855 4134.5802)
    ))
    ; P2670 -- see feature_dimensions_mm.csv
    ("06_ORNAMENT" 0 (
      (12726.855 4134.5802) (12725.9542 4130.0305) (12727.1756 4123.8931) (12727.3435 4123.6489)
    ))
    ; P2671 -- see feature_dimensions_mm.csv
    ("06_ORNAMENT" 0 (
      (12727.3435 4123.6489) (12730.6565 4118.687) (12735.8473 4115.2214) (12741.9847 4114.0) (12748.1221 4115.2214)
      (12753.313 4118.687) (12756.7939 4123.8931) (12758.0153 4130.0305) (12756.7939 4136.1679) (12753.313 4141.3588)
      (12748.1221 4144.8397) (12741.9847 4146.0611) (12735.8473 4144.8397) (12730.6565 4141.3588) (12727.1756 4136.1679)
      (12726.855 4134.5802)
    ))
    ; P2672 -- see feature_dimensions_mm.csv
    ("06_ORNAMENT" 0 (
      (12885.4962 4473.2824) (12992.3664 4473.2824) (13068.7023 4473.2824)
    ))
    ; P2673 -- see feature_dimensions_mm.csv
    ("06_ORNAMENT" 0 (
      (13007.6336 4412.2137) (12992.3664 4412.2137)
    ))
    ; P2674 -- see feature_dimensions_mm.csv
    ("06_ORNAMENT" 0 (
      (12992.3664 3832.0611) (13007.6336 3832.0611)
    ))
    ; P2675 -- see feature_dimensions_mm.csv
    ("06_ORNAMENT" 0 (
      (13068.7023 3679.3893) (13068.7023 3633.5878) (13404.5802 3633.5878) (13435.1145 3633.5878) (13435.1145 3664.1221)
      (13435.1145 3679.3893) (13435.1145 3740.458) (13435.1145 3968.3359)
    ))
    ; P2676 -- see feature_dimensions_mm.csv
    ("06_ORNAMENT" 0 (
      (13160.3053 1778.626) (13148.5038 1776.7634) (13137.8779 1771.3435) (13129.4198 1762.8855) (13124.0 1752.2595)
      (13122.1374 1740.458) (13124.0 1728.6565) (13129.4198 1718.0305) (13137.8779 1709.5725) (13148.5038 1704.1527)
      (13160.3053 1702.2901)
    ))
    ; P2677 -- see feature_dimensions_mm.csv
    ("06_ORNAMENT" 0 (
      (13160.3053 1592.2901) (13159.9084 1592.9771) (13152.7939 1601.9847) (13144.1374 1610.4427) (13134.1527 1618.1527)
      (13123.084 1624.916) (13111.2061 1630.5649) (13098.8092 1634.9618) (13086.2137 1638.0153) (13073.6947 1639.6183)
      (13061.6031 1639.7557) (13050.1985 1638.4122) (13039.7863 1635.6336) (13030.6107 1631.4809) (13022.9008 1626.0458)
      (13016.8397 1619.4656) (13012.5954 1611.9237) (13010.2595 1603.5878) (13009.8931 1594.6565) (13011.5115 1585.374)
      (13015.0534 1575.9389) (13020.4427 1566.6107) (13027.5573 1557.6031) (13036.2137 1549.1298) (13046.1985 1541.4198)
      (13057.2672 1534.6565) (13069.145 1529.0076) (13081.542 1524.6107) (13094.1527 1521.5725) (13106.6565 1519.9542)
      (13118.7634 1519.8168) (13130.1679 1521.1603) (13140.5802 1523.9389) (13149.7557 1528.1069) (13157.4656 1533.542)
      (13160.3053 1536.626)
    ))
    ; P2678 -- see feature_dimensions_mm.csv
    ("06_ORNAMENT" 0 (
      (13190.8397 6155.6183) (13188.8244 6151.5267) (13183.5267 6138.4733) (13179.0687 6124.7328) (13175.5725 6110.5344)
      (13172.3511 6094.4885) (13169.0076 6075.8015) (13166.0458 6055.542) (13164.0153 6034.8092) (13163.4198 6014.687)
      (13164.7939 5996.2595) (13168.6718 5980.626) (13175.5725 5968.855) (13187.6183 5960.9466) (13205.2366 5955.8779)
      (13226.3817 5953.1603) (13248.9771 5952.3664) (13270.9771 5953.0076) (13290.3511 5954.6565) (13305.0382 5956.8244)
      (13312.9771 5959.084) (13313.3588 5961.8473) (13307.771 5965.7252) (13297.8015 5970.5649) (13285.0382 5976.1832)
      (13271.0687 5982.4122) (13257.4962 5989.084) (13245.8931 5996.0153) (13237.8626 6003.0534) (13232.7023 6010.5344)
      (13230.3664 6015.2672)
    ))
    ; P2679 -- see feature_dimensions_mm.csv
    ("06_ORNAMENT" 0 (
      (13435.1145 5605.2519) (13429.8473 5594.4275) (13424.3511 5580.7786) (13419.5115 5566.0916) (13415.4198 5550.626)
      (13412.2137 5534.6565) (13409.2672 5516.6107) (13406.1985 5495.5878) (13403.4809 5472.7939) (13401.6183 5449.4656)
      (13401.0687 5426.8244) (13402.3359 5406.0916) (13405.8931 5388.5038) (13412.2137 5375.2672) (13423.2672 5366.3817)
      (13435.1145 5362.1832)
    ))
    ; P2680 -- see feature_dimensions_mm.csv
    ("06_ORNAMENT" 0 (
      (13435.1145 5362.1832) (13435.1145 5465.6489)
    ))
    ; P2681 -- see feature_dimensions_mm.csv
    ("06_ORNAMENT" 0 (
      (13435.1145 5355.8168) (13435.1145 5362.1832)
    ))
    ; P2682 -- see feature_dimensions_mm.csv
    ("06_ORNAMENT" 0 (
      (13435.1145 5079.2519) (13435.1145 5091.1145) (13435.1145 5092.3053) (13435.1145 5186.7023) (13435.1145 5190.6565)
      (13435.1145 5355.8168)
    ))
    ; P2683 -- see feature_dimensions_mm.csv
    ("06_ORNAMENT" 0 (
      (13435.1145 5355.8168) (13425.9542 5360.6107) (13415.1603 5365.145) (13403.5878 5369.1298) (13391.542 5372.3053)
      (13379.2977 5374.3817) (13367.1603 5375.1145) (13355.4198 5374.2137) (13344.3969 5371.4046) (13334.3511 5366.4122)
      (13324.9618 5359.0687) (13315.8168 5349.5573) (13307.0534 5338.1221) (13298.855 5325.0687) (13291.374 5310.6565)
      (13284.7634 5295.1603) (13279.1908 5278.8397) (13274.8092 5261.9847) (13270.7786 5242.9313) (13266.5954 5220.7328)
      (13262.9008 5196.687) (13260.3511 5172.0611) (13259.6183 5148.1679) (13261.3435 5126.2901) (13266.1832 5107.7099)
      (13274.8092 5093.7405) (13289.8779 5084.3511) (13311.8626 5078.3359) (13293.3282 5059.9237) (13255.9237 5020.2748)
      (13220.7634 4980.2443) (13188.458 4940.229) (13159.5878 4900.6412) (13134.7481 4861.9084) (13114.5038 4824.4275)
      (13138.2901 4837.8321) (13121.374 4816.0305) (13149.1603 4824.7786) (13128.2443 4807.6336) (13155.8321 4808.4733)
      (13135.1145 4799.2366) (13159.0687 4791.7863) (13141.9847 4790.8397) (13155.2214 4780.1527) (13148.855 4782.4427)
      (13155.8473 4768.8702) (13156.458 4742.3817) (13160.3969 4709.2824) (13167.2519 4675.1756) (13176.7023 4640.4733)
      (13188.4122 4605.5878) (13202.0763 4570.916) (13217.374 4536.8855) (13233.9847 4503.9084) (13251.6031 4472.3817)
      (13269.8931 4442.7328) (13283.8473 4422.2748) (13279.1908 4408.6107) (13274.8092 4391.7557) (13270.7786 4372.7023)
      (13266.5954 4350.5038) (13262.9008 4326.458) (13260.3511 4301.8321) (13259.6183 4277.9389) (13261.084 4259.2214)
      (13257.1603 4259.8779) (13245.0229 4260.6107) (13233.2824 4259.7099) (13222.2595 4256.9008) (13212.2137 4251.9084)
      (13202.8244 4244.5649) (13193.6794 4235.0534) (13184.916 4223.6183) (13176.7176 4210.5649) (13169.2366 4196.1527)
      (13162.626 4180.6565) (13157.0534 4164.3359) (13152.6718 4147.4809) (13148.6412 4128.4275) (13144.458 4106.229)
      (13140.7634 4082.1832) (13138.2137 4057.5573) (13137.4809 4033.6641) (13139.2061 4011.7863) (13144.0458 3993.2061)
      (13152.6718 3979.2366) (13167.7405 3969.8473) (13189.7557 3963.8321) (13212.0 3961.1145) (13207.2672 3960.7634)
      (13197.7099 3958.3969) (13189.0076 3954.1985) (13180.8702 3948.0153) (13172.9466 3940.0) (13165.3588 3930.3817)
      (13158.2443 3919.3893) (13151.7557 3907.2519) (13146.0305 3894.1985) (13141.1908 3880.458) (13137.4046 3866.2595)
      (13133.9237 3850.2137) (13130.2901 3831.5267) (13127.084 3811.2672) (13124.8702 3790.5344) (13124.229 3770.4122)
      (13125.7252 3751.9847) (13129.9237 3736.3511) (13137.4046 3724.5802) (13150.458 3716.6718) (13169.542 3711.6031)
      (13192.4427 3708.8855) (13216.916 3708.0916) (13240.7634 3708.7328) (13261.7405 3710.3817) (13277.6489 3712.5496)
      (13286.2595 3714.8092) (13286.6718 3717.5725) (13280.6107 3721.4504) (13269.8168 3726.2901) (13256.0 3731.9084)
      (13240.8702 3738.1374) (13226.1527 3744.8092) (13213.5878 3751.7405) (13204.8855 3758.7786) (13199.2977 3766.2595)
      (13194.8855 3774.5038) (13191.5267 3783.2824) (13189.1298 3792.3664) (13187.5878 3801.5267) (13186.7939 3810.5344)
      (13186.6412 3819.1603) (13187.0229 3827.1756) (13188.1832 3834.9771) (13190.3359 3842.9618) (13193.313 3850.8702)
      (13196.9466 3858.4733) (13201.0687 3865.5267) (13205.542 3871.771) (13210.1679 3876.9924) (13214.8092 3880.916)
      (13220.1679 3883.4962) (13226.687 3884.9466) (13233.8473 3885.4046) (13241.1145 3885.0382) (13247.9389 3884.0)
      (13253.7863 3882.458) (13258.1374 3880.5649) (13260.458 3878.4733) (13260.1069 3875.9847) (13257.3282 3872.8855)
      (13252.8855 3869.2519) (13247.5573 3865.1908) (13242.1069 3860.8092) (13237.2977 3856.1985) (13233.8931 3851.4656)
      (13232.6718 3846.7176) (13233.4809 3841.3588) (13235.5115 3835.0382) (13238.5802 3828.229) (13242.4733 3821.374)
      (13247.0076 3814.9466) (13251.9695 3809.3893) (13254.2137 3807.5725) (13251.9084 3801.5267) (13257.7405 3804.916)
      (13262.4427 3802.7481) (13268.2595 3802.0458) (13275.0534 3802.5802) (13282.458 3804.229) (13290.1069 3806.8702)
      (13297.6489 3810.3664) (13304.7328 3814.5954) (13310.9771 3819.4351) (13316.0305 3824.7328) (13320.3664 3830.916)
      (13324.5191 3838.3053) (13328.229 3846.5649) (13331.2824 3855.4198) (13333.4198 3864.5649) (13333.4809 3865.0687)
      (13339.2519 3870.7634) (13355.8626 3888.6412) (13371.7863 3907.1603) (13386.8855 3926.0458) (13400.9618 3945.0076)
      (13413.8779 3963.7405) (13416.5802 3968.0) (13435.1145 3968.3359)
    ))
    ; P2684 -- see feature_dimensions_mm.csv
    ("06_ORNAMENT" 0 (
      (13435.1145 5073.4504) (13435.1145 5079.2519)
    ))
    ; P2685 -- see feature_dimensions_mm.csv
    ("06_ORNAMENT" 0 (
      (13435.1145 5073.4504) (13407.6031 5057.2519) (13397.1908 5050.6718) (13397.9847 5051.4809) (13422.3206 5077.4504)
      (13435.1145 5079.2519)
    ))
    ; P2686 -- see feature_dimensions_mm.csv
    ("06_ORNAMENT" 0 (
      (13435.1145 4982.4275) (13435.1145 5073.4504)
    ))
    ; P2687 -- see feature_dimensions_mm.csv
    ("06_ORNAMENT" 0 (
      (13435.1145 4959.6031) (13435.1145 4982.4275)
    ))
    ; P2688 -- see feature_dimensions_mm.csv
    ("06_ORNAMENT" 0 (
      (13435.1145 4959.6031) (13392.2748 4945.8931) (13372.1374 4938.6718) (13377.0229 4941.7863) (13419.4656 4970.916)
      (13435.1145 4982.4275)
    ))
    ; P2689 -- see feature_dimensions_mm.csv
    ("06_ORNAMENT" 0 (
      (13435.1145 4876.7786) (13435.1145 4959.6031)
    ))
    ; P2690 -- see feature_dimensions_mm.csv
    ("06_ORNAMENT" 0 (
      (13435.1145 4851.9542) (13435.1145 4876.7786)
    ))
    ; P2691 -- see feature_dimensions_mm.csv
    ("06_ORNAMENT" 0 (
      (13435.1145 4851.9542) (13399.7099 4851.7863) (13360.0153 4850.0611) (13385.4504 4858.3359) (13429.8321 4874.626)
      (13435.1145 4876.7786)
    ))
    ; P2692 -- see feature_dimensions_mm.csv
    ("06_ORNAMENT" 0 (
      (13435.1145 4774.5038) (13435.1145 4851.9542)
    ))
    ; P2693 -- see feature_dimensions_mm.csv
    ("06_ORNAMENT" 0 (
      (13435.1145 4732.9924) (13435.1145 4774.5038)
    ))
    ; P2694 -- see feature_dimensions_mm.csv
    ("06_ORNAMENT" 0 (
      (13435.1145 4732.9924) (13402.3206 4745.6183) (13363.1756 4758.916) (13325.4046 4769.9847) (13328.1374 4769.8931)
      (13370.7786 4770.3359) (13413.4198 4772.5344) (13435.1145 4774.5038)
    ))
    ; P2695 -- see feature_dimensions_mm.csv
    ("06_ORNAMENT" 0 (
      (13435.1145 4653.145) (13435.1145 4732.9924)
    ))
    ; P2696 -- see feature_dimensions_mm.csv
    ("06_ORNAMENT" 0 (
      (13435.1145 4568.7023) (13435.1145 4653.145)
    ))
    ; P2697 -- see feature_dimensions_mm.csv
    ("06_ORNAMENT" 0 (
      (13435.1145 4568.7023) (13422.1527 4583.542) (13394.7481 4612.626) (13365.8779 4640.9924) (13335.8626 4668.2137)
      (13305.0229 4693.8168) (13298.855 4698.4427) (13307.4198 4694.7481) (13346.458 4679.9847) (13386.1527 4666.855)
      (13425.9237 4655.4198) (13435.1145 4653.145)
    ))
    ; P2698 -- see feature_dimensions_mm.csv
    ("06_ORNAMENT" 0 (
      (13435.1145 4490.1679) (13435.1145 4568.7023)
    ))
    ; P2699 -- see feature_dimensions_mm.csv
    ("06_ORNAMENT" 0 (
      (13435.1145 4485.5878) (13435.1145 4490.1679)
    ))
    ; P2700 -- see feature_dimensions_mm.csv
    ("06_ORNAMENT" 0 (
      (13435.1145 4485.5878) (13425.9542 4490.3817) (13415.1603 4494.916) (13403.5878 4498.9008) (13391.542 4502.0763)
      (13379.2977 4504.1527) (13367.1603 4504.8855) (13355.4198 4503.9847) (13344.3969 4501.1756) (13334.3511 4496.1832)
      (13324.9618 4488.8397) (13319.2519 4482.9008) (13311.7863 4508.3206) (13300.0916 4542.8244) (13286.7939 4577.2061)
      (13271.9847 4610.9924) (13264.1832 4626.6718) (13289.0229 4602.5344) (13319.6031 4575.2824) (13350.9313 4549.542)
      (13382.5038 4525.6031) (13413.8321 4503.7405) (13435.1145 4490.1679)
    ))
    ; P2701 -- see feature_dimensions_mm.csv
    ("06_ORNAMENT" 0 (
      (13435.1145 4316.4733) (13435.1145 4485.5878)
    ))
    ; P2702 -- see feature_dimensions_mm.csv
    ("06_ORNAMENT" 0 (
      (13435.1145 4222.9313) (13435.1145 4316.4733)
    ))
    ; P2703 -- see feature_dimensions_mm.csv
    ("06_ORNAMENT" 0 (
      (13435.1145 4222.9313) (13434.6107 4222.3053) (13427.5878 4225.542) (13411.6489 4232.2137) (13394.1832 4239.6183)
      (13377.2214 4247.5267) (13362.7176 4255.771) (13352.6718 4264.1221) (13346.229 4273.0076) (13341.1298 4282.7939)
      (13337.2672 4293.2214) (13334.4885 4304.0) (13332.7176 4314.8855) (13331.7863 4325.5878) (13331.6183 4335.8321)
      (13332.0611 4345.3435) (13333.4046 4354.6107) (13334.8092 4359.9389) (13343.5115 4351.145) (13341.145 4377.4046)
      (13343.5115 4382.5038) (13348.2748 4390.8855) (13353.4198 4398.3053) (13358.7634 4404.4885) (13364.1221 4409.1603)
      (13370.3053 4412.229) (13377.8321 4413.9389) (13386.0916 4414.4885) (13394.4733 4414.0611) (13402.3359 4412.8244)
      (13409.0992 4410.9924) (13414.1221 4408.7481) (13416.7939 4406.2595) (13416.3817 4403.313) (13413.1756 4399.6183)
      (13408.0611 4395.2977) (13401.9084 4390.4885) (13395.6183 4385.2824) (13390.0611 4379.8168) (13386.1374 4374.1985)
      (13384.7328 4368.5496) (13385.6641 4362.1832) (13388.0 4354.687) (13391.542 4346.5954) (13396.0458 4338.458)
      (13401.2672 4330.8244) (13407.0076 4324.229) (13413.0229 4319.2214) (13419.084 4316.3359) (13425.8015 4315.4962)
      (13433.6336 4316.1374) (13435.1145 4316.4733)
    ))
    ; P2704 -- see feature_dimensions_mm.csv
    ("06_ORNAMENT" 0 (
      (13435.1145 4099.8473) (13435.1145 4122.8855) (13435.1145 4152.4885) (13435.1145 4164.0) (13435.1145 4187.8321)
      (13435.1145 4209.0229) (13435.1145 4222.0763) (13435.1145 4222.9313)
    ))
    ; P2705 -- see feature_dimensions_mm.csv
    ("06_ORNAMENT" 0 (
      (13435.1145 4098.2901) (13435.1145 4099.8473)
    ))
    ; P2706 -- see feature_dimensions_mm.csv
    ("06_ORNAMENT" 0 (
      (13435.1145 4098.2901) (13431.0992 4094.2748) (13435.1145 4099.8473)
    ))
    ; P2707 -- see feature_dimensions_mm.csv
    ("06_ORNAMENT" 0 (
      (13435.1145 4096.6718) (13435.1145 4098.2901)
    ))
    ; P2708 -- see feature_dimensions_mm.csv
    ("06_ORNAMENT" 0 (
      (13435.1145 4076.7328) (13435.1145 4096.6718)
    ))
    ; P2709 -- see feature_dimensions_mm.csv
    ("06_ORNAMENT" 0 (
      (13435.1145 4096.6718) (13431.5267 4093.313) (13429.9237 4089.1603) (13430.9771 4084.4733) (13433.6336 4078.9466)
      (13435.1145 4076.7328)
    ))
    ; P2710 -- see feature_dimensions_mm.csv
    ("06_ORNAMENT" 0 (
      (13435.1145 4047.0687) (13435.1145 4076.7328)
    ))
    ; P2711 -- see feature_dimensions_mm.csv
    ("06_ORNAMENT" 0 (
      (13435.1145 4020.3969) (13435.1145 4047.0687)
    ))
    ; P2712 -- see feature_dimensions_mm.csv
    ("06_ORNAMENT" 0 (
      (13435.1145 4020.3969) (13419.542 4008.9466) (13412.4885 4003.2824) (13405.542 4005.8473) (13414.9771 4018.4427)
      (13432.5802 4043.2672) (13435.1145 4047.0687)
    ))
    ; P2713 -- see feature_dimensions_mm.csv
    ("06_ORNAMENT" 0 (
      (13435.1145 3998.7176) (13435.1145 4020.3969)
    ))
    ; P2714 -- see feature_dimensions_mm.csv
    ("06_ORNAMENT" 0 (
      (13435.1145 3995.8321) (13435.1145 3998.7176)
    ))
    ; P2715 -- see feature_dimensions_mm.csv
    ("06_ORNAMENT" 0 (
      (13435.1145 3995.8321) (13433.6947 3996.2595) (13435.1145 3998.7176)
    ))
    ; P2716 -- see feature_dimensions_mm.csv
    ("06_ORNAMENT" 0 (
      (13435.1145 3968.3359) (13435.1145 3995.8321)
    ))
    ; P2717 -- see feature_dimensions_mm.csv
    ("06_ORNAMENT" 1 (
      (1258.0153 7374.0458) (1259.374 7371.5267) (1263.084 7369.4809) (1268.1221 7368.1527) (1273.1756 7367.4656)
      (1276.9618 7367.0076) (1278.6412 7366.1527) (1278.0458 7364.3511) (1275.7099 7361.3435) (1272.626 7357.2824)
      (1270.0 7352.7786) (1268.8244 7348.7176) (1269.6489 7345.9847) (1272.3817 7345.1603) (1276.4427 7346.3359)
      (1280.9466 7348.9618) (1285.0076 7352.0458) (1288.0153 7354.3817) (1289.8168 7354.9771) (1290.6718 7353.2977)
      (1291.1298 7349.5115) (1291.8321 7344.458) (1293.145 7339.4198) (1295.1908 7335.7099) (1297.7099 7334.3511)
      (1300.229 7335.7099) (1302.2748 7339.4198) (1303.6031 7344.458) (1304.2901 7349.5115) (1304.7481 7353.2977)
      (1305.6031 7354.9771) (1307.4046 7354.3817) (1310.4122 7352.0458) (1314.4733 7348.9618) (1318.9771 7346.3359)
      (1323.0382 7345.1603) (1325.771 7345.9847) (1326.5954 7348.7176) (1325.4198 7352.7786) (1322.7939 7357.2824)
      (1319.7099 7361.3435) (1317.374 7364.3511) (1316.7786 7366.1527) (1318.458 7367.0076) (1322.2443 7367.4656)
      (1327.2977 7368.1527) (1332.3359 7369.4809) (1336.0458 7371.5267) (1337.4046 7374.0458) (1336.0458 7376.5649)
      (1332.3359 7378.6107) (1327.2977 7379.9237) (1322.2443 7380.626) (1318.458 7381.084) (1316.7786 7381.9389)
      (1317.374 7383.7405) (1319.7099 7386.7481) (1322.7939 7390.8092) (1325.4198 7395.313) (1326.5954 7399.374)
      (1325.771 7402.1069) (1323.0382 7402.9313) (1318.9771 7401.7557) (1314.4733 7399.1298) (1310.4122 7396.0458)
      (1307.4046 7393.7099) (1305.6031 7393.1145) (1304.7481 7394.7939) (1304.2901 7398.5802) (1303.6031 7403.6336)
      (1302.2748 7408.6718) (1300.229 7412.3817) (1297.7099 7413.7405) (1295.1908 7412.3817) (1293.145 7408.6718)
      (1291.8321 7403.6336) (1291.1298 7398.5802) (1290.6718 7394.7939) (1289.8168 7393.1145) (1288.0153 7393.7099)
      (1285.0076 7396.0458) (1280.9466 7399.1298) (1276.4427 7401.7557) (1272.3817 7402.9313) (1269.6489 7402.1069)
      (1268.8244 7399.374) (1270.0 7395.313) (1272.626 7390.8092) (1275.7099 7386.7481) (1278.0458 7383.7405)
      (1278.6412 7381.9389) (1276.9618 7381.084) (1273.1756 7380.626) (1268.1221 7379.9237) (1263.084 7378.6107)
      (1259.374 7376.5649)
    ))
    ; P2718 -- see feature_dimensions_mm.csv
    ("06_ORNAMENT" 1 (
      (1258.0153 7206.1069) (1259.374 7203.5878) (1263.084 7201.542) (1268.1221 7200.2137) (1273.1756 7199.5267)
      (1276.9618 7199.0687) (1278.6412 7198.2137) (1278.0458 7196.4122) (1275.7099 7193.4046) (1272.626 7189.3435)
      (1270.0 7184.8397) (1268.8244 7180.7786) (1269.6489 7178.0458) (1272.3817 7177.2214) (1276.4427 7178.3969)
      (1280.9466 7181.0229) (1285.0076 7184.1069) (1288.0153 7186.4427) (1289.8168 7187.0382) (1290.6718 7185.3588)
      (1291.1298 7181.5725) (1291.8321 7176.5191) (1293.145 7171.4809) (1295.1908 7167.771) (1297.7099 7166.4122)
      (1300.229 7167.771) (1302.2748 7171.4809) (1303.6031 7176.5191) (1304.2901 7181.5725) (1304.7481 7185.3588)
      (1305.6031 7187.0382) (1307.4046 7186.4427) (1310.4122 7184.1069) (1314.4733 7181.0229) (1318.9771 7178.3969)
      (1323.0382 7177.2214) (1325.771 7178.0458) (1326.5954 7180.7786) (1325.4198 7184.8397) (1322.7939 7189.3435)
      (1319.7099 7193.4046) (1317.374 7196.4122) (1316.7786 7198.2137) (1318.458 7199.0687) (1322.2443 7199.5267)
      (1327.2977 7200.2137) (1332.3359 7201.542) (1336.0458 7203.5878) (1337.4046 7206.1069) (1336.0458 7208.626)
      (1332.3359 7210.6718) (1327.2977 7211.9847) (1322.2443 7212.687) (1318.458 7213.145) (1316.7786 7214.0)
      (1317.374 7215.8015) (1319.7099 7218.8092) (1322.7939 7222.8702) (1325.4198 7227.374) (1326.5954 7231.4351)
      (1325.771 7234.1679) (1323.0382 7234.9924) (1318.9771 7233.8168) (1314.4733 7231.1908) (1310.4122 7228.1069)
      (1307.4046 7225.771) (1305.6031 7225.1756) (1304.7481 7226.855) (1304.2901 7230.6412) (1303.6031 7235.6947)
      (1302.2748 7240.7328) (1300.229 7244.4427) (1297.7099 7245.8015) (1295.1908 7244.4427) (1293.145 7240.7328)
      (1291.8321 7235.6947) (1291.1298 7230.6412) (1290.6718 7226.855) (1289.8168 7225.1756) (1288.0153 7225.771)
      (1285.0076 7228.1069) (1280.9466 7231.1908) (1276.4427 7233.8168) (1272.3817 7234.9924) (1269.6489 7234.1679)
      (1268.8244 7231.4351) (1270.0 7227.374) (1272.626 7222.8702) (1275.7099 7218.8092) (1278.0458 7215.8015)
      (1278.6412 7214.0) (1276.9618 7213.145) (1273.1756 7212.687) (1268.1221 7211.9847) (1263.084 7210.6718)
      (1259.374 7208.626)
    ))
    ; P2719 -- see feature_dimensions_mm.csv
    ("06_ORNAMENT" 1 (
      (1288.5802 7374.0458) (1289.2824 7370.5496) (1291.2519 7367.5878) (1294.2137 7365.6183) (1297.7099 7364.916)
      (1301.2061 7365.6183) (1304.1679 7367.5878) (1306.1374 7370.5496) (1306.8397 7374.0458) (1306.1374 7377.542)
      (1304.1679 7380.5038) (1301.2061 7382.4733) (1297.7099 7383.1756) (1294.2137 7382.4733) (1291.2519 7380.5038)
      (1289.2824 7377.542)
    ))
    ; P2720 -- see feature_dimensions_mm.csv
    ("06_ORNAMENT" 1 (
      (1288.5802 7206.1069) (1289.2824 7202.6107) (1291.2519 7199.6489) (1294.2137 7197.6794) (1297.7099 7196.9771)
      (1301.2061 7197.6794) (1304.1679 7199.6489) (1306.1374 7202.6107) (1306.8397 7206.1069) (1306.1374 7209.6031)
      (1304.1679 7212.5649) (1301.2061 7214.5344) (1297.7099 7215.2366) (1294.2137 7214.5344) (1291.2519 7212.5649)
      (1289.2824 7209.6031)
    ))
    ; P2721 -- see feature_dimensions_mm.csv
    ("06_ORNAMENT" 1 (
      (1375.4046 3886.3511) (1376.3053 3877.8015) (1378.2901 3869.2214) (1381.0992 3860.9313) (1384.5344 3853.1756)
      (1388.3664 3846.2595) (1392.3664 3840.458) (1397.0382 3835.4809) (1402.7939 3830.9618) (1409.3282 3826.9924)
      (1416.3053 3823.7099) (1423.3588 3821.2366) (1430.1985 3819.6794) (1436.458 3819.1756) (1441.8321 3819.8473)
      (1446.687 3822.1221) (1451.4962 3826.0763) (1456.0763 3831.2824) (1460.2748 3837.313) (1463.8626 3843.7252)
      (1466.687 3850.1221) (1468.5649 3856.0458) (1469.313 3861.0687) (1468.1832 3865.5267) (1465.0534 3869.9542)
      (1460.6107 3874.2748) (1455.5725 3878.3817) (1450.6565 3882.1985) (1446.5496 3885.6031) (1443.9847 3888.5191)
      (1443.6641 3890.8397) (1445.8015 3892.7939) (1449.8168 3894.5802) (1455.2214 3896.0305) (1461.5267 3896.9924)
      (1468.229 3897.3435) (1474.8397 3896.9008) (1480.855 3895.5573) (1485.8015 3893.1298) (1490.0916 3889.4504)
      (1494.3664 3884.5649) (1498.4733 3878.7023) (1502.2901 3872.0916) (1505.6489 3864.9618) (1508.3817 3857.542)
      (1510.3664 3850.0611) (1511.4504 3842.7481) (1511.8015 3835.2366) (1511.6641 3827.145) (1510.9313 3818.7023)
      (1509.5115 3810.1069) (1507.2977 3801.6031) (1504.1985 3793.374) (1500.1221 3785.6336) (1494.9618 3778.626)
      (1486.9313 3772.0305) (1475.3282 3765.5267) (1461.7557 3759.2824) (1447.7863 3753.4351) (1435.0229 3748.1679)
      (1425.0534 3743.6336) (1419.4656 3739.9847) (1419.8473 3737.4046) (1427.7863 3735.2977) (1442.4733 3733.2519)
      (1461.8473 3731.7099) (1483.8626 3731.0992) (1506.4427 3731.8626) (1527.5878 3734.3969) (1545.2061 3739.1603)
      (1557.2519 3746.5649) (1564.1527 3757.5878) (1568.0305 3772.2595) (1569.4046 3789.5267) (1568.8244 3808.3969)
      (1566.7786 3827.8321) (1563.8168 3846.8244) (1560.4733 3864.3511) (1557.2519 3879.3893) (1553.7557 3892.7023)
      (1549.2977 3905.5878) (1544.0 3917.8168) (1538.0153 3929.1908) (1531.4504 3939.4962) (1524.4427 3948.5191)
      (1517.1298 3956.0305) (1509.6183 3961.8321) (1501.5878 3965.771) (1492.7634 3967.9847) (1483.374 3968.7023)
      (1473.6641 3968.1221) (1463.8779 3966.4885) (1454.229 3963.9847) (1444.9771 3960.8244) (1436.3359 3957.2519)
      (1427.8015 3952.8397) (1418.9313 3947.2214) (1410.0611 3940.626) (1401.5267 3933.3435) (1393.6794 3925.6183)
      (1386.8702 3917.6947) (1381.4351 3909.8321) (1377.7099 3902.2901) (1375.8015 3894.6107)
    ))
    ; P2722 -- see feature_dimensions_mm.csv
    ("06_ORNAMENT" 1 (
      (1521.8321 5548.3969) (1523.7863 5550.7481) (1527.4809 5552.8855) (1532.4275 5554.626) (1538.2137 5555.7863)
      (1544.3511 5556.1985) (1550.4122 5555.6794) (1555.9237 5554.0458) (1560.458 5551.145) (1564.3817 5546.7176)
      (1568.3053 5540.855) (1572.0763 5533.8321) (1575.5725 5525.8931) (1578.6412 5517.3435) (1581.1603 5508.4427)
      (1582.9771 5499.4656) (1583.9695 5490.687) (1584.2901 5481.6641) (1584.1679 5471.9695) (1583.4962 5461.8321)
      (1582.1832 5451.5267) (1580.1527 5441.313) (1577.313 5431.4351) (1573.5725 5422.1527) (1572.6107 5420.4427)
      (1567.0687 5433.0992) (1554.626 5457.6489) (1541.0382 5481.2824) (1537.9084 5486.1527) (1540.3511 5491.8626)
      (1542.9466 5499.5267) (1544.6565 5506.6412) (1545.3435 5512.6718) (1544.3053 5518.0153) (1541.4351 5523.3435)
      (1537.3588 5528.5191) (1532.7481 5533.4504) (1528.2443 5538.0153) (1524.4885 5542.1069) (1522.1374 5545.6031)
    ))
    ; P2723 -- see feature_dimensions_mm.csv
    ("06_ORNAMENT" 1 (
      (1580.5802 4324.3817) (1587.1603 4321.2366) (1596.0 4318.0916) (1604.5344 4316.1374) (1612.3664 4315.4962)
      (1619.084 4316.3359) (1625.145 4319.2214) (1631.1603 4324.229) (1636.9008 4330.8244) (1642.1221 4338.458)
      (1646.626 4346.5954) (1650.1679 4354.687) (1652.5038 4362.1832) (1653.4351 4368.5496) (1652.0305 4374.1985)
      (1648.1069 4379.8168) (1642.5496 4385.2824) (1636.2595 4390.4885) (1630.1069 4395.2977) (1624.9924 4399.6183)
      (1621.7863 4403.313) (1621.374 4406.2595) (1624.0458 4408.7481) (1629.0687 4410.9924) (1635.8321 4412.8244)
      (1643.7099 4414.0611) (1652.0763 4414.4885) (1660.3359 4413.9389) (1667.8626 4412.229) (1674.0458 4409.1603)
      (1679.4046 4404.4885) (1684.7481 4398.3053) (1689.8931 4390.8855) (1694.6565 4382.5038) (1696.3664 4378.8092)
      (1696.0611 4376.458) (1694.6565 4351.145) (1703.2366 4360.4275) (1704.7634 4354.6107) (1706.1069 4345.3435)
      (1706.5496 4335.8321) (1706.3817 4325.5878) (1705.4504 4314.8855) (1703.6794 4304.0) (1700.9008 4293.2214)
      (1697.0382 4282.7939) (1691.9389 4273.0076) (1685.4962 4264.1221) (1675.4504 4255.771) (1660.9466 4247.5267)
      (1643.9847 4239.6183) (1626.5344 4232.2137) (1610.5802 4225.542) (1603.8473 4222.4427) (1601.8015 4225.1145)
      (1601.2824 4238.4733) (1598.9008 4256.6107) (1595.4504 4274.3359) (1591.542 4290.7023) (1587.7863 4304.7328)
      (1583.7099 4317.1603)
    ))
    ; P2724 -- see feature_dimensions_mm.csv
    ("06_ORNAMENT" 1 (
      (1580.7176 4120.458) (1588.1374 4121.7557) (1600.7786 4103.4046) (1605.6336 4096.6565) (1594.8702 4107.313)
    ))
    ; P2725 -- see feature_dimensions_mm.csv
    ("06_ORNAMENT" 1 (
      (1610.4885 5185.8779) (1612.3664 5185.7252) (1619.084 5186.5649) (1625.145 5189.4504) (1631.1603 5194.458)
      (1636.9008 5201.0534) (1642.1221 5208.687) (1646.626 5216.8244) (1650.1679 5224.916) (1652.5038 5232.4122)
      (1653.4351 5238.7786) (1652.0305 5244.4275) (1648.1069 5250.0458) (1642.5496 5255.5115) (1636.2595 5260.7176)
      (1630.1069 5265.5267) (1624.9924 5269.8473) (1621.7863 5273.542) (1621.374 5276.4885) (1624.0458 5278.9771)
      (1629.0687 5281.2214) (1635.8321 5283.0534) (1643.7099 5284.2901) (1652.0763 5284.7176) (1660.3359 5284.1679)
      (1667.8626 5282.458) (1674.0458 5279.3893) (1679.4046 5274.7176) (1684.7481 5268.5344) (1689.8931 5261.1145)
      (1694.6565 5252.7328) (1698.855 5243.7099) (1702.2748 5234.3206) (1704.7634 5224.8397) (1706.1069 5215.5725)
      (1706.5496 5206.0611) (1706.3817 5195.8168) (1705.4504 5185.1145) (1703.6794 5174.229) (1700.9008 5163.4504)
      (1697.0382 5153.0229) (1691.9389 5143.2366) (1685.4962 5134.3511) (1676.4275 5126.8092) (1656.3969 5145.5878)
      (1616.0916 5181.2061)
    ))
    ; P2726 -- see feature_dimensions_mm.csv
    ("06_ORNAMENT" 1 (
      (1615.4809 4207.2672) (1619.8931 4206.6565) (1644.1069 4204.7023) (1671.6183 4203.9237) (1679.4656 4204.1985)
      (1672.5191 4196.0) (1665.7252 4186.0458) (1664.4733 4183.4809) (1653.9695 4186.8855) (1641.4504 4188.9466)
      (1629.0076 4189.5725) (1628.0305 4190.9008)
    ))
    ; P2727 -- see feature_dimensions_mm.csv
    ("06_ORNAMENT" 1 (
      (1618.3206 5816.7939) (1632.2443 5798.0305) (1648.626 5778.5649) (1667.1908 5758.7176) (1673.0229 5753.0382)
      (1674.6107 5748.2595) (1678.4427 5739.0382) (1682.4427 5731.2977) (1687.1145 5724.6718) (1692.8702 5718.626)
      (1699.4046 5713.3435) (1706.3817 5708.9618) (1713.4351 5705.6641) (1720.2748 5703.6031) (1726.5344 5702.9313)
      (1729.1145 5703.3588) (1733.3588 5699.8931) (1757.9847 5681.5725) (1783.4656 5664.4122) (1790.8855 5659.9389)
      (1790.1985 5658.1985) (1785.0382 5648.855) (1777.0076 5640.0611) (1765.4046 5631.3893) (1751.8321 5623.0534)
      (1737.8626 5615.2672) (1725.0992 5608.2443) (1715.1298 5602.1985) (1709.542 5597.3435) (1709.9237 5593.8931)
      (1717.8626 5591.084) (1732.5496 5588.3511) (1751.9237 5586.3053) (1773.9389 5585.4962) (1796.5191 5586.5038)
      (1817.6641 5589.8779) (1835.2824 5596.229) (1847.3282 5606.1069) (1854.229 5620.8092) (1855.2672 5626.0763)
      (1862.2595 5622.9466) (1888.4122 5613.5115) (1914.0611 5606.7786) (1938.9313 5603.0534) (1924.6107 5625.4656)
      (1907.3282 5647.3435) (1887.4962 5668.5649) (1865.5115 5688.9771) (1858.3969 5694.8092) (1856.855 5714.4733)
      (1853.8931 5739.7863) (1850.5496 5763.1603) (1847.3282 5783.2061) (1843.8321 5800.9466) (1839.374 5818.1221)
      (1834.0763 5834.4427) (1828.0916 5849.6183) (1821.5267 5863.3588) (1814.5191 5875.374) (1807.2061 5885.4046)
      (1799.6947 5893.1298) (1791.6641 5898.3817) (1782.8397 5901.3282) (1773.4504 5902.2901) (1763.7405 5901.5267)
      (1753.9542 5899.3282) (1744.3053 5895.9847) (1735.0534 5891.7863) (1726.4122 5887.0229) (1717.8779 5881.145)
      (1709.0076 5873.6336) (1700.1374 5864.8702) (1691.6031 5855.145) (1683.7557 5844.8397) (1676.9466 5834.2748)
      (1671.5115 5823.8015) (1667.7863 5813.7405) (1666.0153 5804.2901) (1661.8931 5805.771) (1639.1298 5812.4122)
    ))
    ; P2728 -- see feature_dimensions_mm.csv
    ("06_ORNAMENT" 1 (
      (1680.7481 6117.9542) (1681.6489 6108.8397) (1683.6336 6099.6947) (1686.4427 6090.8397) (1689.8779 6082.5802)
      (1693.7099 6075.1908) (1697.7099 6069.0076) (1702.3817 6063.7099) (1708.1374 6058.8702) (1714.6718 6054.6412)
      (1721.6489 6051.145) (1728.7023 6048.5038) (1735.542 6046.855) (1741.8015 6046.3206) (1747.1756 6047.0229)
      (1752.0305 6049.4504) (1756.8397 6053.6641) (1761.4198 6059.2214) (1765.6183 6065.6489) (1769.2061 6072.5038)
      (1772.0305 6079.313) (1773.9084 6085.6336) (1774.6565 6090.9924) (1773.5267 6095.7405) (1770.3969 6100.4733)
      (1765.9542 6105.084) (1760.916 6109.4656) (1756.0 6113.5267) (1751.8931 6117.1603) (1749.3282 6120.2595)
      (1749.0076 6122.7481) (1751.145 6124.8397) (1755.1603 6126.7328) (1760.5649 6128.2748) (1766.8702 6129.313)
      (1773.5725 6129.6794) (1780.1832 6129.2214) (1786.1985 6127.771) (1791.145 6125.1908) (1795.4351 6121.2672)
      (1799.7099 6116.0458) (1803.8168 6109.8015) (1807.6336 6102.7481) (1810.9924 6095.145) (1813.7252 6087.2366)
      (1815.7099 6079.2519) (1816.7939 6071.4504) (1817.145 6063.4351) (1817.0076 6054.8092) (1816.2748 6045.8015)
      (1814.855 6036.6412) (1812.6412 6027.5573) (1809.542 6018.7786) (1805.4656 6010.5344) (1800.3053 6003.0534)
      (1792.2748 5996.0153) (1780.6718 5989.084) (1767.0992 5982.4122) (1753.1298 5976.1832) (1740.3664 5970.5649)
      (1730.3969 5965.7252) (1724.8092 5961.8473) (1725.1908 5959.084) (1733.1298 5956.8244) (1747.8168 5954.6565)
      (1767.1908 5953.0076) (1789.2061 5952.3664) (1811.7863 5953.1603) (1832.9313 5955.8779) (1850.5496 5960.9466)
      (1862.5954 5968.855) (1869.4962 5980.626) (1873.374 5996.2595) (1874.7481 6014.687) (1874.1679 6034.8092)
      (1872.1221 6055.542) (1869.1603 6075.8015) (1865.8168 6094.4885) (1862.5954 6110.5344) (1859.0992 6124.7328)
      (1854.6412 6138.4733) (1849.3435 6151.5267) (1843.3588 6163.6641) (1836.7939 6174.6565) (1829.7863 6184.2748)
      (1822.4733 6192.2901) (1814.9618 6198.4733) (1806.9313 6202.6718) (1798.1069 6205.0382) (1788.7176 6205.8015)
      (1779.0076 6205.1908) (1769.2214 6203.4351) (1759.5725 6200.7634) (1750.3206 6197.4046) (1741.6794 6193.5878)
      (1733.145 6188.8855) (1724.2748 6182.8855) (1715.4046 6175.8626) (1706.8702 6168.0916) (1699.0229 6159.8473)
      (1692.2137 6151.3893) (1686.7786 6143.0076) (1683.0534 6134.9618) (1681.145 6126.7634)
    ))
    ; P2729 -- see feature_dimensions_mm.csv
    ("06_ORNAMENT" 1 (
      (1733.7405 5798.4733) (1735.8779 5801.084) (1739.8931 5803.4656) (1745.2977 5805.3893) (1751.6031 5806.6718)
      (1758.3053 5807.1298) (1764.916 5806.5649) (1770.9313 5804.7634) (1775.8779 5801.5267) (1780.1679 5796.6107)
      (1784.4427 5790.1069) (1788.5496 5782.2901) (1792.3664 5773.4656) (1795.7252 5763.9695) (1798.458 5754.0763)
      (1800.4427 5744.1069) (1801.2366 5737.0382) (1790.855 5743.8931) (1764.4122 5759.6031) (1758.6412 5762.7023)
      (1758.2595 5764.7176) (1755.1298 5770.6412) (1750.687 5776.3969) (1745.6489 5781.8626) (1740.7328 5786.9466)
      (1736.626 5791.4809) (1734.0611 5795.374)
    ))
    ; P2730 -- see feature_dimensions_mm.csv
    ("06_ORNAMENT" 1 (
      (1742.855 4072.8397) (1747.2824 4074.9466) (1753.2977 4079.9542) (1759.0382 4086.5496) (1764.2595 4094.1832)
      (1768.7634 4102.3206) (1772.3053 4110.4122) (1774.6412 4117.9084) (1775.5725 4124.2748) (1774.1679 4129.9237)
      (1770.2443 4135.542) (1764.687 4141.0076) (1758.3969 4146.2137) (1752.2443 4151.0229) (1747.1298 4155.3435)
      (1743.9237 4159.0382) (1743.5115 4161.9847) (1746.1832 4164.4733) (1751.2061 4166.7176) (1757.9695 4168.5496)
      (1765.8473 4169.7863) (1774.2137 4170.2137) (1782.4733 4169.6641) (1790.0 4167.9542) (1796.1832 4164.8855)
      (1801.542 4160.2137) (1806.8855 4154.0305) (1812.0305 4146.6107) (1816.7939 4138.229) (1820.9924 4129.2061)
      (1824.4122 4119.8168) (1826.9008 4110.3359) (1828.2443 4101.0687) (1828.687 4091.5573) (1828.5191 4081.313)
      (1827.5878 4070.6107) (1825.8168 4059.7252) (1823.0382 4048.9466) (1819.1756 4038.5191) (1814.0763 4028.7328)
      (1807.6336 4019.8473) (1797.5878 4011.4962) (1783.084 4003.2519) (1766.1221 3995.3435) (1759.084 3992.3511)
      (1751.4504 4006.3817) (1748.6718 4011.0534) (1750.0458 4022.3969) (1749.2061 4040.0) (1746.3206 4058.1374)
    ))
    ; P2731 -- see feature_dimensions_mm.csv
    ("06_ORNAMENT" 1 (
      (1746.5649 7374.0458) (1747.9237 7371.5267) (1751.6336 7369.4809) (1756.6718 7368.1527) (1761.7252 7367.4656)
      (1765.5115 7367.0076) (1767.1908 7366.1527) (1766.5954 7364.3511) (1764.2595 7361.3435) (1761.1756 7357.2824)
      (1758.5496 7352.7786) (1757.374 7348.7176) (1758.1985 7345.9847) (1760.9313 7345.1603) (1764.9924 7346.3359)
      (1769.4962 7348.9618) (1773.5573 7352.0458) (1776.5649 7354.3817) (1778.3664 7354.9771) (1779.2214 7353.2977)
      (1779.6794 7349.5115) (1780.3817 7344.458) (1781.6947 7339.4198) (1783.7405 7335.7099) (1786.2595 7334.3511)
      (1788.7786 7335.7099) (1790.8244 7339.4198) (1792.1527 7344.458) (1792.8397 7349.5115) (1793.2977 7353.2977)
      (1794.1527 7354.9771) (1795.9542 7354.3817) (1798.9618 7352.0458) (1803.0229 7348.9618) (1807.5267 7346.3359)
      (1811.5878 7345.1603) (1814.3206 7345.9847) (1815.145 7348.7176) (1813.9695 7352.7786) (1811.3435 7357.2824)
      (1808.2595 7361.3435) (1805.9237 7364.3511) (1805.3282 7366.1527) (1807.0076 7367.0076) (1810.7939 7367.4656)
      (1815.8473 7368.1527) (1820.8855 7369.4809) (1824.5954 7371.5267) (1825.9542 7374.0458) (1824.5954 7376.5649)
      (1820.8855 7378.6107) (1815.8473 7379.9237) (1810.7939 7380.626) (1807.0076 7381.084) (1805.3282 7381.9389)
      (1805.9237 7383.7405) (1808.2595 7386.7481) (1811.3435 7390.8092) (1813.9695 7395.313) (1815.145 7399.374)
      (1814.3206 7402.1069) (1811.5878 7402.9313) (1807.5267 7401.7557) (1803.0229 7399.1298) (1798.9618 7396.0458)
      (1795.9542 7393.7099) (1794.1527 7393.1145) (1793.2977 7394.7939) (1792.8397 7398.5802) (1792.1527 7403.6336)
      (1790.8244 7408.6718) (1788.7786 7412.3817) (1786.2595 7413.7405) (1783.7405 7412.3817) (1781.6947 7408.6718)
      (1780.3817 7403.6336) (1779.6794 7398.5802) (1779.2214 7394.7939) (1778.3664 7393.1145) (1776.5649 7393.7099)
      (1773.5573 7396.0458) (1769.4962 7399.1298) (1764.9924 7401.7557) (1760.9313 7402.9313) (1758.1985 7402.1069)
      (1757.374 7399.374) (1758.5496 7395.313) (1761.1756 7390.8092) (1764.2595 7386.7481) (1766.5954 7383.7405)
      (1767.1908 7381.9389) (1765.5115 7381.084) (1761.7252 7380.626) (1756.6718 7379.9237) (1751.6336 7378.6107)
      (1747.9237 7376.5649)
    ))
    ; P2732 -- see feature_dimensions_mm.csv
    ("06_ORNAMENT" 1 (
      (1746.5649 7206.1069) (1747.9237 7203.5878) (1751.6336 7201.542) (1756.6718 7200.2137) (1761.7252 7199.5267)
      (1765.5115 7199.0687) (1767.1908 7198.2137) (1766.5954 7196.4122) (1764.2595 7193.4046) (1761.1756 7189.3435)
      (1758.5496 7184.8397) (1757.374 7180.7786) (1758.1985 7178.0458) (1760.9313 7177.2214) (1764.9924 7178.3969)
      (1769.4962 7181.0229) (1773.5573 7184.1069) (1776.5649 7186.4427) (1778.3664 7187.0382) (1779.2214 7185.3588)
      (1779.6794 7181.5725) (1780.3817 7176.5191) (1781.6947 7171.4809) (1783.7405 7167.771) (1786.2595 7166.4122)
      (1788.7786 7167.771) (1790.8244 7171.4809) (1792.1527 7176.5191) (1792.8397 7181.5725) (1793.2977 7185.3588)
      (1794.1527 7187.0382) (1795.9542 7186.4427) (1798.9618 7184.1069) (1803.0229 7181.0229) (1807.5267 7178.3969)
      (1811.5878 7177.2214) (1814.3206 7178.0458) (1815.145 7180.7786) (1813.9695 7184.8397) (1811.3435 7189.3435)
      (1808.2595 7193.4046) (1805.9237 7196.4122) (1805.3282 7198.2137) (1807.0076 7199.0687) (1810.7939 7199.5267)
      (1815.8473 7200.2137) (1820.8855 7201.542) (1824.5954 7203.5878) (1825.9542 7206.1069) (1824.5954 7208.626)
      (1820.8855 7210.6718) (1815.8473 7211.9847) (1810.7939 7212.687) (1807.0076 7213.145) (1805.3282 7214.0)
      (1805.9237 7215.8015) (1808.2595 7218.8092) (1811.3435 7222.8702) (1813.9695 7227.374) (1815.145 7231.4351)
      (1814.3206 7234.1679) (1811.5878 7234.9924) (1807.5267 7233.8168) (1803.0229 7231.1908) (1798.9618 7228.1069)
      (1795.9542 7225.771) (1794.1527 7225.1756) (1793.2977 7226.855) (1792.8397 7230.6412) (1792.1527 7235.6947)
      (1790.8244 7240.7328) (1788.7786 7244.4427) (1786.2595 7245.8015) (1783.7405 7244.4427) (1781.6947 7240.7328)
      (1780.3817 7235.6947) (1779.6794 7230.6412) (1779.2214 7226.855) (1778.3664 7225.1756) (1776.5649 7225.771)
      (1773.5573 7228.1069) (1769.4962 7231.1908) (1764.9924 7233.8168) (1760.9313 7234.9924) (1758.1985 7234.1679)
      (1757.374 7231.4351) (1758.5496 7227.374) (1761.1756 7222.8702) (1764.2595 7218.8092) (1766.5954 7215.8015)
      (1767.1908 7214.0) (1765.5115 7213.145) (1761.7252 7212.687) (1756.6718 7211.9847) (1751.6336 7210.6718)
      (1747.9237 7208.626)
    ))
    ; P2733 -- see feature_dimensions_mm.csv
    ("06_ORNAMENT" 1 (
      (1750.855 3961.6641) (1762.6718 3960.7176) (1773.4046 3950.7939) (1769.771 3949.313) (1760.5954 3944.6412)
      (1757.374 3950.6565)
    ))
    ; P2734 -- see feature_dimensions_mm.csv
    ("06_ORNAMENT" 1 (
      (1775.9389 3960.1527) (1793.7557 3959.6489) (1804.855 3960.0305) (1799.6031 3959.1603) (1789.1603 3956.4885)
      (1779.3282 3953.1908)
    ))
    ; P2735 -- see feature_dimensions_mm.csv
    ("06_ORNAMENT" 1 (
      (1777.1298 7374.0458) (1777.8321 7370.5496) (1779.8015 7367.5878) (1782.7634 7365.6183) (1786.2595 7364.916)
      (1789.7557 7365.6183) (1792.7176 7367.5878) (1794.687 7370.5496) (1795.3893 7374.0458) (1794.687 7377.542)
      (1792.7176 7380.5038) (1789.7557 7382.4733) (1786.2595 7383.1756) (1782.7634 7382.4733) (1779.8015 7380.5038)
      (1777.8321 7377.542)
    ))
    ; P2736 -- see feature_dimensions_mm.csv
    ("06_ORNAMENT" 1 (
      (1777.1298 7206.1069) (1777.8321 7202.6107) (1779.8015 7199.6489) (1782.7634 7197.6794) (1786.2595 7196.9771)
      (1789.7557 7197.6794) (1792.7176 7199.6489) (1794.687 7202.6107) (1795.3893 7206.1069) (1794.687 7209.6031)
      (1792.7176 7212.5649) (1789.7557 7214.5344) (1786.2595 7215.2366) (1782.7634 7214.5344) (1779.8015 7212.5649)
      (1777.8321 7209.6031)
    ))
    ; P2737 -- see feature_dimensions_mm.csv
    ("06_ORNAMENT" 1 (
      (1803.8779 1885.4809) (1809.0382 1878.9313) (1817.6947 1870.4733) (1827.6794 1862.7634) (1838.7481 1856.0)
      (1850.626 1850.3511) (1863.0229 1845.9542) (1875.6183 1842.9008) (1888.1374 1841.2977) (1900.2443 1841.1603)
      (1911.6336 1842.5038) (1922.0458 1845.2824) (1931.2214 1849.4351) (1938.9313 1854.8702) (1944.9924 1861.4504)
      (1949.2366 1868.9924) (1951.5725 1877.3282) (1951.9389 1886.2595) (1950.3206 1895.542) (1946.7786 1904.9771)
      (1941.3893 1914.3053) (1934.2748 1923.313) (1925.6183 1931.7863) (1915.6336 1939.4962) (1904.5649 1946.2595)
      (1892.687 1951.9084) (1880.2901 1956.3053) (1867.6794 1959.3435) (1855.1756 1960.9618) (1843.0687 1961.0992)
      (1831.6641 1959.7557) (1821.2519 1956.9771) (1816.9618 1955.0229) (1810.3206 1928.2748) (1805.4504 1900.4733)
    ))
    ; P2738 -- see feature_dimensions_mm.csv
    ("06_ORNAMENT" 1 (
      (1862.5954 1740.458) (1864.2901 1728.5191) (1869.313 1716.8702) (1877.5725 1705.8015) (1888.8397 1695.5878)
      (1902.8397 1686.4733) (1919.2366 1678.7023) (1937.6183 1672.4427) (1957.542 1667.8626) (1978.5038 1665.0687)
      (2000.0 1664.1221) (2021.4962 1665.0687) (2042.458 1667.8626) (2062.3817 1672.4427) (2080.7634 1678.7023)
      (2097.1603 1686.4733) (2111.1603 1695.5878) (2122.4275 1705.8015) (2130.687 1716.8702) (2135.7099 1728.5191)
      (2137.4046 1740.458) (2135.7099 1752.3969) (2130.687 1764.0458) (2122.4275 1775.1145) (2111.1603 1785.3282)
      (2097.1603 1794.4427) (2080.7634 1802.2137) (2062.3817 1808.4733) (2042.458 1813.0534) (2021.4962 1815.8473)
      (2000.0 1816.7939) (1978.5038 1815.8473) (1957.542 1813.0534) (1937.6183 1808.4733) (1919.2366 1802.2137)
      (1902.8397 1794.4427) (1888.8397 1785.3282) (1877.5725 1775.1145) (1869.313 1764.0458) (1864.2901 1752.3969)
    ))
    ; P2739 -- see feature_dimensions_mm.csv
    ("06_ORNAMENT" 1 (
      (1877.8626 5954.1985) (1896.9771 5938.9313) (1918.7634 5923.5267) (1942.8702 5908.2443) (1968.9466 5893.313)
      (1996.626 5878.9618) (2025.5725 5865.4656) (2055.4046 5853.0382) (2085.7863 5841.9542) (2116.3511 5832.4122)
      (2146.7481 5824.7023) (2176.626 5819.0382) (2205.6183 5815.6641) (2233.374 5814.8397) (2259.542 5816.7939)
      (2239.0534 5835.542) (2215.6947 5853.1145) (2189.9542 5869.4504) (2162.2443 5884.5191) (2133.0534 5898.2595)
      (2102.8092 5910.6107) (2071.9847 5921.5573) (2041.0229 5931.0229) (2010.3817 5938.9618) (1980.5191 5945.3435)
      (1951.8779 5950.1069) (1924.916 5953.2061) (1900.0916 5954.5802)
    ))
    ; P2740 -- see feature_dimensions_mm.csv
    ("06_ORNAMENT" 1 (
      (1897.5115 2064.3206) (1899.374 2052.5344) (1904.7939 2041.8931) (1913.2366 2033.4504) (1923.8779 2028.0305)
      (1935.6794 2026.1527) (1947.4656 2028.0305) (1958.1069 2033.4504) (1966.5496 2041.8931) (1971.9695 2052.5344)
      (1973.8473 2064.3206) (1971.9695 2076.1221) (1966.5496 2086.7634) (1958.1069 2095.2061) (1947.4656 2100.626)
      (1935.6794 2102.4885) (1923.8779 2100.626) (1913.2366 2095.2061) (1904.7939 2086.7634) (1899.374 2076.1221)
    ))
    ; P2741 -- see feature_dimensions_mm.csv
    ("06_ORNAMENT" 1 (
      (1897.5115 1416.5954) (1899.374 1404.7939) (1904.7939 1394.1527) (1913.2366 1385.7099) (1923.8779 1380.2901)
      (1935.6794 1378.4275) (1941.5878 1379.3588) (1940.1679 1377.9695) (1938.9313 1374.0458) (1940.1679 1370.1221)
      (1943.7099 1366.6412) (1948.9771 1363.8931) (1955.1756 1362.0305) (1961.3588 1360.9313) (1966.7023 1360.2443)
      (1970.5191 1359.5115) (1972.5038 1358.1679) (1972.6718 1355.7863) (1971.4046 1352.1069) (1969.3282 1347.145)
      (1967.1756 1341.2214) (1965.6947 1334.9313) (1965.4351 1329.0076) (1966.687 1324.1985) (1969.4656 1321.1603)
      (1973.4809 1320.2748) (1978.2748 1321.5878) (1983.2824 1324.7786) (1987.9847 1329.2214) (1992.0458 1334.0305)
      (1995.2977 1338.3053) (1997.8473 1341.2519) (2000.0 1342.2901) (2002.1527 1341.2519) (2004.7023 1338.3053)
      (2007.9542 1334.0305) (2012.0153 1329.2214) (2016.7176 1324.7786) (2021.7252 1321.5878) (2026.5191 1320.2748)
      (2030.5344 1321.1603) (2033.313 1324.1985) (2034.5649 1329.0076) (2034.3053 1334.9313) (2032.8244 1341.2214)
      (2030.6718 1347.145) (2028.5954 1352.1069) (2027.3282 1355.7863) (2027.4962 1358.1679) (2029.4809 1359.5115)
      (2033.2977 1360.2443) (2038.6412 1360.9313) (2043.9237 1361.8779) (2043.6947 1361.2061) (2040.6565 1348.5954)
      (2039.0382 1336.0916) (2038.9008 1323.9847) (2040.2443 1312.5802) (2043.0229 1302.1679) (2047.1908 1292.9924)
      (2052.626 1285.2824) (2059.1908 1279.2366) (2066.7328 1274.9924) (2075.084 1272.6565) (2084.0 1272.2901)
      (2093.2977 1273.8931) (2102.7176 1277.4504) (2112.0611 1282.8397) (2121.0687 1289.9542) (2129.5267 1298.6107)
      (2137.2366 1308.5954) (2144.0 1319.6641) (2149.6489 1331.542) (2154.0458 1343.9389) (2157.0992 1356.5344)
      (2158.7023 1369.0534) (2158.8397 1381.145) (2157.4962 1392.5496) (2154.7176 1402.9618) (2150.5649 1412.1374)
      (2145.1298 1419.8473) (2138.5496 1425.9084) (2131.0076 1430.1527) (2122.6718 1432.4885) (2113.7405 1432.855)
      (2104.458 1431.2366) (2095.0229 1427.6947) (2085.6947 1422.3053) (2076.687 1415.1908) (2068.2137 1406.5344)
      (2060.5038 1396.5496) (2053.7405 1385.4809) (2052.7176 1383.313) (2051.0229 1384.1985) (2044.8244 1386.0611)
      (2038.6412 1387.1603) (2033.2977 1387.8473) (2029.4809 1388.5802) (2027.4962 1389.9237) (2027.3282 1392.3053)
      (2028.5954 1395.9847) (2030.6718 1400.9466) (2032.8244 1406.8702) (2034.3053 1413.1603) (2034.5649 1419.084)
      (2033.313 1423.8931) (2030.5344 1426.9313) (2026.5191 1427.8168) (2021.7252 1426.5038) (2016.7176 1423.313)
      (2012.0153 1418.8702) (2007.9542 1414.0611) (2004.7023 1409.7863) (2002.1527 1406.8397) (2000.0 1405.8015)
      (1997.8473 1406.8397) (1995.2977 1409.7863) (1992.0458 1414.0611) (1987.9847 1418.8702) (1983.2824 1423.313)
      (1978.2748 1426.5038) (1973.4809 1427.8168) (1972.1069 1427.5115) (1971.9695 1428.3817) (1966.5496 1439.0229)
      (1958.1069 1447.4656) (1947.4656 1452.8855) (1935.6794 1454.7634) (1923.8779 1452.8855) (1913.2366 1447.4656)
      (1904.7939 1439.0229) (1899.374 1428.3817)
    ))
    ; P2742 -- see feature_dimensions_mm.csv
    ("06_ORNAMENT" 1 (
      (1902.687 6056.5496) (1903.9695 6050.8397) (1906.7634 6045.1298) (1910.7634 6039.6031) (1915.6336 6034.4275)
      (1921.0534 6029.8168) (1926.7176 6025.9542) (1933.3282 6022.6412) (1941.4962 6019.6183) (1950.7481 6016.9771)
      (1960.626 6014.7939) (1970.626 6013.145) (1980.3053 6012.1069) (1989.1908 6011.771) (1996.7939 6012.2137)
      (2003.6641 6013.7252) (2010.4733 6016.3664) (2016.9771 6019.8321) (2022.916 6023.8473) (2028.0 6028.1374)
      (2032.0153 6032.3969) (2034.6718 6036.3359) (2035.7252 6039.6947) (2034.1221 6042.6718) (2029.6794 6045.6183)
      (2023.3893 6048.5038) (2016.2595 6051.2366) (2009.2824 6053.771) (2003.4809 6056.0458) (1999.8473 6057.9847)
      (1999.3893 6059.542) (2002.4122 6060.855) (2008.1069 6062.0305) (2015.771 6062.9924) (2024.7023 6063.6489)
      (2034.1832 6063.8779) (2043.5573 6063.5878) (2052.0763 6062.687) (2059.084 6061.0687) (2065.145 6058.6107)
      (2071.2061 6055.3588) (2077.0382 6051.4504) (2082.4427 6047.0382) (2087.1908 6042.2901) (2091.084 6037.3435)
      (2093.8931 6032.3511) (2095.4198 6027.4809) (2095.9237 6022.4733) (2095.7252 6017.084) (2094.687 6011.4504)
      (2092.6565 6005.7252) (2089.5267 6000.0458) (2085.145 5994.5649) (2079.3588 5989.4046) (2072.0611 5984.7328)
      (2060.6718 5980.3359) (2044.2443 5976.0) (2025.0076 5971.8321) (2005.2366 5967.9389) (1987.145 5964.4275)
      (1973.0229 5961.4046) (1965.1145 5958.9771) (1965.6489 5957.2519) (1976.9008 5955.8473) (1997.7099 5954.4885)
      (2025.145 5953.4656) (2056.3206 5953.0534) (2088.3359 5953.5573) (2118.2748 5955.2519) (2143.2366 5958.4275)
      (2160.3053 5963.3588) (2170.0763 5970.7176) (2175.5725 5980.4885) (2177.5267 5992.0) (2176.687 6004.5802)
      (2173.8015 6017.542) (2169.6183 6030.1985) (2164.8702 6041.8779) (2160.3053 6051.9084) (2155.3435 6060.7786)
      (2149.0382 6069.374) (2141.542 6077.5267) (2134.0458 6084.229) (2153.1603 6073.2061) (2183.7557 6057.1298)
      (2216.1527 6041.6031) (2232.5954 6034.4427) (2232.8244 6033.5878) (2235.374 6033.2214) (2249.9084 6026.8855)
      (2284.626 6013.2519) (2319.8779 6000.9313) (2355.2366 5990.2137) (2390.3053 5981.3282) (2424.626 5974.5496)
      (2457.8168 5970.1527) (2489.4504 5968.3664) (2519.084 5969.4656) (2494.5954 5989.2366) (2466.9313 6007.8931)
      (2436.6107 6025.374) (2405.8626 6040.7939) (2413.2061 6047.0534) (2418.0458 6056.8244) (2419.771 6068.3359)
      (2419.0382 6080.916) (2416.4885 6093.8779) (2412.7939 6106.5344) (2408.6107 6118.2137) (2404.5802 6128.2443)
      (2400.1985 6137.1145) (2394.626 6145.7099) (2388.0153 6153.8626) (2380.5344 6161.4504) (2372.3359 6168.3206)
      (2363.5725 6174.3359) (2354.4275 6179.3435) (2345.0382 6183.2061) (2334.9924 6185.8321) (2323.9695 6187.313)
      (2312.229 6187.7863) (2300.0916 6187.4046) (2287.8473 6186.3053) (2275.8015 6184.6412) (2264.229 6182.5344)
      (2253.4351 6180.1527) (2242.7786 6177.2061) (2231.6794 6173.4656) (2220.5802 6169.0687) (2209.9237 6164.2137)
      (2200.1221 6159.0687) (2191.6031 6153.7863) (2184.8092 6148.5344) (2180.1527 6143.5115) (2177.7557 6138.3969)
      (2177.2672 6132.8855) (2178.3969 6127.1756) (2180.8702 6121.4656) (2184.3969 6115.9389) (2188.687 6110.7634)
      (2188.9924 6110.4733) (2160.7634 6115.4656) (2129.9084 6119.5267) (2101.6031 6121.771) (2076.3359 6122.1374)
      (2099.0382 6105.9695) (2104.3664 6102.5649) (2103.4656 6103.0076) (2092.8244 6106.8702) (2081.4504 6109.4962)
      (2068.9313 6110.9771) (2055.6489 6111.4504) (2041.8931 6111.0687) (2028.0153 6109.9695) (2014.3511 6108.3053)
      (2001.2366 6106.1985) (1989.0076 6103.8168) (1976.916 6100.8702) (1964.3511 6097.1298) (1951.7863 6092.7328)
      (1939.6947 6087.8779) (1928.5802 6082.7328) (1918.9313 6077.4504) (1911.2214 6072.1985) (1905.9542 6067.1756)
      (1903.2519 6062.0611)
    ))
    ; P2743 -- see feature_dimensions_mm.csv
    ("06_ORNAMENT" 1 (
      (1938.9313 2137.4046) (1940.1679 2133.4809) (1943.7099 2130.0) (1948.9771 2127.2519) (1955.1756 2125.3893)
      (1961.3588 2124.2901) (1966.7023 2123.6031) (1970.5191 2122.8702) (1972.5038 2121.5267) (1972.6718 2119.145)
      (1971.4046 2115.4656) (1969.3282 2110.5038) (1967.1756 2104.5802) (1965.6947 2098.2901) (1965.4351 2092.3664)
      (1966.687 2087.5573) (1969.4656 2084.5191) (1973.4809 2083.6336) (1978.2748 2084.9466) (1983.2824 2088.1374)
      (1987.9847 2092.5802) (1992.0458 2097.3893) (1995.2977 2101.6641) (1997.8473 2104.6107) (2000.0 2105.6489)
      (2002.1527 2104.6107) (2004.7023 2101.6641) (2007.9542 2097.3893) (2012.0153 2092.5802) (2016.7176 2088.1374)
      (2021.7252 2084.9466) (2026.5191 2083.6336) (2030.5344 2084.5191) (2033.313 2087.5573) (2034.5649 2092.3664)
      (2034.3053 2098.2901) (2032.8244 2104.5802) (2030.6718 2110.5038) (2028.5954 2115.4656) (2027.3282 2119.145)
      (2027.4962 2121.5267) (2029.4809 2122.8702) (2033.2977 2123.6031) (2038.6412 2124.2901) (2042.4275 2124.9618)
      (2043.6947 2119.7099) (2048.0916 2107.313) (2053.7405 2095.4351) (2060.5038 2084.3664) (2068.2137 2074.3817)
      (2076.687 2065.7252) (2085.6947 2058.6107) (2095.0229 2053.2214) (2104.458 2049.6794) (2113.7405 2048.0611)
      (2122.6718 2048.4275) (2131.0076 2050.7634) (2138.5496 2055.0076) (2145.1298 2061.0687) (2150.5649 2068.7786)
      (2154.7176 2077.9542) (2157.4962 2088.3664) (2158.8397 2099.7557) (2158.7023 2111.8626) (2157.0992 2124.3817)
      (2154.0458 2136.9771) (2149.6489 2149.374) (2144.0 2161.2519) (2137.2366 2172.3206) (2129.5267 2182.3053)
      (2121.0687 2190.9618) (2112.0611 2198.0763) (2102.7176 2203.4656) (2093.2977 2207.0229) (2084.0 2208.626)
      (2075.084 2208.2595) (2066.7328 2205.9237) (2059.1908 2201.6794) (2052.626 2195.6336) (2047.1908 2187.9237)
      (2043.0229 2178.7481) (2040.2443 2168.3359) (2038.9008 2156.9313) (2038.9771 2150.458) (2038.6412 2150.5191)
      (2033.2977 2151.2061) (2029.4809 2151.9389) (2027.4962 2153.2824) (2027.3282 2155.6641) (2028.5954 2159.3435)
      (2030.6718 2164.3053) (2032.8244 2170.229) (2034.3053 2176.5191) (2034.5649 2182.4427) (2033.313 2187.2519)
      (2030.5344 2190.2901) (2026.5191 2191.1756) (2021.7252 2189.8626) (2016.7176 2186.6718) (2012.0153 2182.229)
      (2007.9542 2177.4198) (2004.7023 2173.145) (2002.1527 2170.1985) (2000.0 2169.1603) (1997.8473 2170.1985)
      (1995.2977 2173.145) (1992.0458 2177.4198) (1987.9847 2182.229) (1983.2824 2186.6718) (1982.5954 2187.0992)
      (1980.7176 2185.8473) (1966.1527 2174.5954) (1967.1756 2170.229) (1969.3282 2164.3053) (1971.4046 2159.3435)
      (1972.6718 2155.6641) (1972.5038 2153.2824) (1970.5191 2151.9389) (1966.7023 2151.2061) (1961.3588 2150.5191)
      (1955.1756 2149.4198) (1948.9771 2147.5573) (1943.7099 2144.8092) (1940.1679 2141.3282)
    ))
    ; P2744 -- see feature_dimensions_mm.csv
    ("06_ORNAMENT" 1 (
      (1959.1603 1386.7634) (1966.5496 1394.1527) (1969.6336 1400.1985) (1971.4046 1395.9847) (1972.6718 1392.3053)
      (1972.5038 1389.9237) (1970.5191 1388.5802) (1966.7023 1387.8473) (1961.3588 1387.1603)
    ))
    ; P2745 -- see feature_dimensions_mm.csv
    ("06_ORNAMENT" 1 (
      (1964.9466 1986.0458) (1965.6947 1970.855) (1969.145 1954.5191) (1975.2366 1937.4198) (1983.8168 1920.0)
      (1994.6565 1902.6718) (2007.5115 1885.8626) (2022.0458 1870.0) (2037.9084 1855.4656) (2054.7023 1842.626)
      (2072.0305 1831.771) (2089.4656 1823.2061) (2106.5496 1817.1145) (2122.9008 1813.6489) (2138.0763 1812.9008)
      (2151.7405 1814.9008) (2163.542 1819.5725) (2173.1756 1826.8244) (2180.4275 1836.458) (2185.0992 1848.2595)
      (2187.0992 1861.9237) (2186.3511 1877.0992) (2182.8855 1893.4504) (2176.7939 1910.5344) (2168.229 1927.9695)
      (2157.374 1945.2977) (2144.5344 1962.0916) (2130.0 1977.9542) (2114.1374 1992.4885) (2097.3282 2005.3435)
      (2080.0 2016.1832) (2062.5802 2024.7634) (2045.4809 2030.855) (2029.145 2034.3053) (2013.9542 2035.0534)
      (2000.2901 2033.0687) (1988.5038 2028.3817) (1978.855 2021.145) (1971.6183 2011.4962) (1966.9313 1999.7099)
    ))
    ; P2746 -- see feature_dimensions_mm.csv
    ("06_ORNAMENT" 1 (
      (1964.9466 1494.8702) (1966.9313 1481.2061) (1971.6183 1469.4198) (1978.855 1459.771) (1988.5038 1452.5191)
      (2000.2901 1447.8473) (2013.9542 1445.8626) (2029.145 1446.5954) (2045.4809 1450.0611) (2062.5802 1456.1527)
      (2080.0 1464.7328) (2097.3282 1475.5725) (2114.1374 1488.4275) (2130.0 1502.9618) (2144.5344 1518.8244)
      (2157.374 1535.6183) (2168.229 1552.9466) (2176.7939 1570.3817) (2182.8855 1587.4656) (2186.3511 1603.8168)
      (2187.0992 1618.9924) (2185.0992 1632.6565) (2180.4275 1644.458) (2173.1756 1654.0916) (2163.542 1661.3435)
      (2151.7405 1666.0153) (2138.0763 1668.0153) (2122.9008 1667.2672) (2106.5496 1663.8015) (2089.4656 1657.7099)
      (2072.0305 1649.145) (2054.7023 1638.2901) (2037.9084 1625.4504) (2022.0458 1610.916) (2007.5115 1595.0534)
      (1994.6565 1578.2443) (1983.8168 1560.916) (1975.2366 1543.4962) (1969.145 1526.3969) (1965.6947 1510.0611)
    ))
    ; P2747 -- see feature_dimensions_mm.csv
    ("06_ORNAMENT" 1 (
      (1979.2366 3007.6336) (1979.9542 3006.3206) (1981.8779 3005.2519) (1984.5191 3004.5496) (1987.1603 3004.1985)
      (1989.145 3003.9542) (1990.0305 3003.4962) (1989.7252 3002.5649) (1988.4885 3000.9924) (1986.8855 2998.8702)
      (1985.5115 2996.5038) (1984.8855 2994.3817) (1985.313 2992.9466) (1986.7481 2992.5191) (1988.8702 2993.145)
      (1991.2366 2994.5191) (1993.3588 2996.1221) (1994.9313 2997.3588) (1995.8626 2997.6641) (1996.3206 2996.7786)
      (1996.5649 2994.7939) (1996.916 2992.1527) (1997.6183 2989.5115) (1998.687 2987.5878) (2000.0 2986.8702)
      (2001.313 2987.5878) (2002.3817 2989.5115) (2003.084 2992.1527) (2003.4351 2994.7939) (2003.6794 2996.7786)
      (2004.1374 2997.6641) (2005.0687 2997.3588) (2006.6412 2996.1221) (2008.7634 2994.5191) (2011.1298 2993.145)
      (2013.2519 2992.5191) (2014.687 2992.9466) (2015.1145 2994.3817) (2014.4885 2996.5038) (2013.1145 2998.8702)
      (2011.5115 3000.9924) (2010.2748 3002.5649) (2009.9695 3003.4962) (2010.855 3003.9542) (2012.8397 3004.1985)
      (2015.4809 3004.5496) (2018.1221 3005.2519) (2020.0458 3006.3206) (2020.7634 3007.6336) (2020.0458 3008.9466)
      (2018.1221 3010.0153) (2015.4809 3010.7176) (2012.8397 3011.0687) (2010.855 3011.313) (2009.9695 3011.771)
      (2010.2748 3012.7023) (2011.5115 3014.2748) (2013.1145 3016.3969) (2014.4885 3018.7634) (2015.1145 3020.8855)
      (2014.687 3022.3206) (2013.2519 3022.7481) (2011.1298 3022.1221) (2008.7634 3020.7481) (2006.6412 3019.145)
      (2005.0687 3017.9084) (2004.1374 3017.6031) (2003.6794 3018.4885) (2003.4351 3020.4733) (2003.084 3023.1145)
      (2002.3817 3025.7557) (2001.313 3027.6794) (2000.0 3028.3969) (1998.687 3027.6794) (1997.6183 3025.7557)
      (1996.916 3023.1145) (1996.5649 3020.4733) (1996.3206 3018.4885) (1995.8626 3017.6031) (1994.9313 3017.9084)
      (1993.3588 3019.145) (1991.2366 3020.7481) (1988.8702 3022.1221) (1986.7481 3022.7481) (1985.313 3022.3206)
      (1984.8855 3020.8855) (1985.5115 3018.7634) (1986.8855 3016.3969) (1988.4885 3014.2748) (1989.7252 3012.7023)
      (1990.0305 3011.771) (1989.145 3011.313) (1987.1603 3011.0687) (1984.5191 3010.7176) (1981.8779 3010.0153)
      (1979.9542 3008.9466)
    ))
    ; P2748 -- see feature_dimensions_mm.csv
    ("06_ORNAMENT" 1 (
      (1979.2366 2900.7634) (1979.9542 2899.4504) (1981.8779 2898.3817) (1984.5191 2897.6794) (1987.1603 2897.3282)
      (1989.145 2897.084) (1990.0305 2896.626) (1989.7252 2895.6947) (1988.4885 2894.1221) (1986.8855 2892.0)
      (1985.5115 2889.6336) (1984.8855 2887.5115) (1985.313 2886.0763) (1986.7481 2885.6489) (1988.8702 2886.2748)
      (1991.2366 2887.6489) (1993.3588 2889.2519) (1994.9313 2890.4885) (1995.8626 2890.7939) (1996.3206 2889.9084)
      (1996.5649 2887.9237) (1996.916 2885.2824) (1997.6183 2882.6412) (1998.687 2880.7176) (2000.0 2880.0)
      (2001.313 2880.7176) (2002.3817 2882.6412) (2003.084 2885.2824) (2003.4351 2887.9237) (2003.6794 2889.9084)
      (2004.1374 2890.7939) (2005.0687 2890.4885) (2006.6412 2889.2519) (2008.7634 2887.6489) (2011.1298 2886.2748)
      (2013.2519 2885.6489) (2014.687 2886.0763) (2015.1145 2887.5115) (2014.4885 2889.6336) (2013.1145 2892.0)
      (2011.5115 2894.1221) (2010.2748 2895.6947) (2009.9695 2896.626) (2010.855 2897.084) (2012.8397 2897.3282)
      (2015.4809 2897.6794) (2018.1221 2898.3817) (2020.0458 2899.4504) (2020.7634 2900.7634) (2020.0458 2902.0763)
      (2018.1221 2903.145) (2015.4809 2903.8473) (2012.8397 2904.1985) (2010.855 2904.4427) (2009.9695 2904.9008)
      (2010.2748 2905.8321) (2011.5115 2907.4046) (2013.1145 2909.5267) (2014.4885 2911.8931) (2015.1145 2914.0153)
      (2014.687 2915.4504) (2013.2519 2915.8779) (2011.1298 2915.2519) (2008.7634 2913.8779) (2006.6412 2912.2748)
      (2005.0687 2911.0382) (2004.1374 2910.7328) (2003.6794 2911.6183) (2003.4351 2913.6031) (2003.084 2916.2443)
      (2002.3817 2918.8855) (2001.313 2920.8092) (2000.0 2921.5267) (1998.687 2920.8092) (1997.6183 2918.8855)
      (1996.916 2916.2443) (1996.5649 2913.6031) (1996.3206 2911.6183) (1995.8626 2910.7328) (1994.9313 2911.0382)
      (1993.3588 2912.2748) (1991.2366 2913.8779) (1988.8702 2915.2519) (1986.7481 2915.8779) (1985.313 2915.4504)
      (1984.8855 2914.0153) (1985.5115 2911.8931) (1986.8855 2909.5267) (1988.4885 2907.4046) (1989.7252 2905.8321)
      (1990.0305 2904.9008) (1989.145 2904.4427) (1987.1603 2904.1985) (1984.5191 2903.8473) (1981.8779 2903.145)
      (1979.9542 2902.0763)
    ))
    ; P2749 -- see feature_dimensions_mm.csv
    ("06_ORNAMENT" 1 (
      (1993.8931 3007.6336) (1994.3511 3005.2977) (1995.6794 3003.313) (1997.6641 3001.9847) (2000.0 3001.5267)
      (2002.3359 3001.9847) (2004.3206 3003.313) (2005.6489 3005.2977) (2006.1069 3007.6336) (2005.6489 3009.9695)
      (2004.3206 3011.9542) (2002.3359 3013.2824) (2000.0 3013.7405) (1997.6641 3013.2824) (1995.6794 3011.9542)
      (1994.3511 3009.9695)
    ))
    ; P2750 -- see feature_dimensions_mm.csv
    ("06_ORNAMENT" 1 (
      (1993.8931 2900.7634) (1994.3511 2898.4275) (1995.6794 2896.4427) (1997.6641 2895.1145) (2000.0 2894.6565)
      (2002.3359 2895.1145) (2004.3206 2896.4427) (2005.6489 2898.4275) (2006.1069 2900.7634) (2005.6489 2903.0992)
      (2004.3206 2905.084) (2002.3359 2906.4122) (2000.0 2906.8702) (1997.6641 2906.4122) (1995.6794 2905.084)
      (1994.3511 2903.0992)
    ))
    ; P2751 -- see feature_dimensions_mm.csv
    ("06_ORNAMENT" 1 (
      (2152.6718 1740.458) (2154.7328 1719.6031) (2160.8092 1699.5573) (2170.687 1681.084) (2183.9695 1664.8855)
      (2200.1679 1651.6031) (2218.6412 1641.7252) (2238.687 1635.6336) (2259.542 1633.5878) (2280.3969 1635.6336)
      (2300.4427 1641.7252) (2318.916 1651.6031) (2335.1145 1664.8855) (2348.3969 1681.084) (2358.2748 1699.5573)
      (2364.3664 1719.6031) (2366.4122 1740.458) (2364.3664 1761.313) (2358.2748 1781.3588) (2348.3969 1799.8321)
      (2335.1145 1816.0305) (2318.916 1829.313) (2300.4427 1839.1908) (2280.3969 1845.2672) (2259.542 1847.3282)
      (2238.687 1845.2672) (2218.6412 1839.1908) (2200.1679 1829.313) (2183.9695 1816.0305) (2170.687 1799.8321)
      (2160.8092 1781.3588) (2154.7328 1761.313)
    ))
    ; P2752 -- see feature_dimensions_mm.csv
    ("06_ORNAMENT" 1 (
      (2183.2061 2000.0) (2184.1527 1978.5038) (2186.9466 1957.542) (2191.5267 1937.6183) (2197.7863 1919.2366)
      (2205.5573 1902.8397) (2214.6718 1888.8397) (2224.8855 1877.5725) (2235.9542 1869.313) (2247.6031 1864.2901)
      (2259.542 1862.5954) (2271.4809 1864.2901) (2283.1298 1869.313) (2294.1985 1877.5725) (2304.4122 1888.8397)
      (2313.5267 1902.8397) (2321.2977 1919.2366) (2327.5573 1937.6183) (2332.1374 1957.542) (2334.9313 1978.5038)
      (2335.8779 2000.0) (2334.9313 2021.4962) (2332.1374 2042.458) (2327.5573 2062.3817) (2321.2977 2080.7634)
      (2313.5267 2097.1603) (2304.4122 2111.1603) (2294.1985 2122.4275) (2283.1298 2130.687) (2271.4809 2135.7099)
      (2259.542 2137.4046) (2247.6031 2135.7099) (2235.9542 2130.687) (2224.8855 2122.4275) (2214.6718 2111.1603)
      (2205.5573 2097.1603) (2197.7863 2080.7634) (2191.5267 2062.3817) (2186.9466 2042.458) (2184.1527 2021.4962)
    ))
    ; P2753 -- see feature_dimensions_mm.csv
    ("06_ORNAMENT" 1 (
      (2183.2061 1740.458) (2184.6718 1725.5725) (2189.0229 1711.2519) (2196.0763 1698.0458) (2205.5573 1686.4733)
      (2217.1298 1676.9924) (2230.3359 1669.9389) (2244.6565 1665.5878) (2259.542 1664.1221) (2274.4275 1665.5878)
      (2288.7481 1669.9389) (2301.9542 1676.9924) (2313.5267 1686.4733) (2323.0076 1698.0458) (2330.0611 1711.2519)
      (2334.4122 1725.5725) (2335.8779 1740.458) (2334.4122 1755.3435) (2330.0611 1769.6641) (2323.0076 1782.8702)
      (2313.5267 1794.4427) (2301.9542 1803.9237) (2288.7481 1810.9771) (2274.4275 1815.3282) (2259.542 1816.7939)
      (2244.6565 1815.3282) (2230.3359 1810.9771) (2217.1298 1803.9237) (2205.5573 1794.4427) (2196.0763 1782.8702)
      (2189.0229 1769.6641) (2184.6718 1755.3435)
    ))
    ; P2754 -- see feature_dimensions_mm.csv
    ("06_ORNAMENT" 1 (
      (2183.2061 1480.916) (2184.1527 1459.4198) (2186.9466 1438.458) (2191.5267 1418.5344) (2197.7863 1400.1527)
      (2205.5573 1383.7557) (2214.6718 1369.7557) (2224.8855 1358.4885) (2235.9542 1350.229) (2247.6031 1345.2061)
      (2259.542 1343.5115) (2271.4809 1345.2061) (2283.1298 1350.229) (2294.1985 1358.4885) (2304.4122 1369.7557)
      (2313.5267 1383.7557) (2321.2977 1400.1527) (2327.5573 1418.5344) (2332.1374 1438.458) (2334.9313 1459.4198)
      (2335.8779 1480.916) (2334.9313 1502.4122) (2332.1374 1523.374) (2327.5573 1543.2977) (2321.2977 1561.6794)
      (2313.5267 1578.0763) (2304.4122 1592.0763) (2294.1985 1603.3435) (2283.1298 1611.6031) (2271.4809 1616.626)
      (2259.542 1618.3206) (2247.6031 1616.626) (2235.9542 1611.6031) (2224.8855 1603.3435) (2214.6718 1592.0763)
      (2205.5573 1578.0763) (2197.7863 1561.6794) (2191.5267 1543.2977) (2186.9466 1523.374) (2184.1527 1502.4122)
    ))
    ; P2755 -- see feature_dimensions_mm.csv
    ("06_ORNAMENT" 1 (
      (2219.8473 7374.0458) (2221.2061 7371.5267) (2224.916 7369.4809) (2229.9542 7368.1527) (2235.0076 7367.4656)
      (2238.7939 7367.0076) (2240.4733 7366.1527) (2239.8779 7364.3511) (2237.542 7361.3435) (2234.458 7357.2824)
      (2231.8321 7352.7786) (2230.6565 7348.7176) (2231.4809 7345.9847) (2234.2137 7345.1603) (2238.2748 7346.3359)
      (2242.7786 7348.9618) (2246.8397 7352.0458) (2249.8473 7354.3817) (2251.6489 7354.9771) (2252.5038 7353.2977)
      (2252.9618 7349.5115) (2253.6641 7344.458) (2254.9771 7339.4198) (2257.0229 7335.7099) (2259.542 7334.3511)
      (2262.0611 7335.7099) (2264.1069 7339.4198) (2265.4351 7344.458) (2266.1221 7349.5115) (2266.5802 7353.2977)
      (2267.4351 7354.9771) (2269.2366 7354.3817) (2272.2443 7352.0458) (2276.3053 7348.9618) (2280.8092 7346.3359)
      (2284.8702 7345.1603) (2287.6031 7345.9847) (2288.4275 7348.7176) (2287.2519 7352.7786) (2284.626 7357.2824)
      (2281.542 7361.3435) (2279.2061 7364.3511) (2278.6107 7366.1527) (2280.2901 7367.0076) (2284.0763 7367.4656)
      (2289.1298 7368.1527) (2294.1679 7369.4809) (2297.8779 7371.5267) (2299.2366 7374.0458) (2297.8779 7376.5649)
      (2294.1679 7378.6107) (2289.1298 7379.9237) (2284.0763 7380.626) (2280.2901 7381.084) (2278.6107 7381.9389)
      (2279.2061 7383.7405) (2281.542 7386.7481) (2284.626 7390.8092) (2287.2519 7395.313) (2288.4275 7399.374)
      (2287.6031 7402.1069) (2284.8702 7402.9313) (2280.8092 7401.7557) (2276.3053 7399.1298) (2272.2443 7396.0458)
      (2269.2366 7393.7099) (2267.4351 7393.1145) (2266.5802 7394.7939) (2266.1221 7398.5802) (2265.4351 7403.6336)
      (2264.1069 7408.6718) (2262.0611 7412.3817) (2259.542 7413.7405) (2257.0229 7412.3817) (2254.9771 7408.6718)
      (2253.6641 7403.6336) (2252.9618 7398.5802) (2252.5038 7394.7939) (2251.6489 7393.1145) (2249.8473 7393.7099)
      (2246.8397 7396.0458) (2242.7786 7399.1298) (2238.2748 7401.7557) (2234.2137 7402.9313) (2231.4809 7402.1069)
      (2230.6565 7399.374) (2231.8321 7395.313) (2234.458 7390.8092) (2237.542 7386.7481) (2239.8779 7383.7405)
      (2240.4733 7381.9389) (2238.7939 7381.084) (2235.0076 7380.626) (2229.9542 7379.9237) (2224.916 7378.6107)
      (2221.2061 7376.5649)
    ))
    ; P2756 -- see feature_dimensions_mm.csv
    ("06_ORNAMENT" 1 (
      (2219.8473 7206.1069) (2221.2061 7203.5878) (2224.916 7201.542) (2229.9542 7200.2137) (2235.0076 7199.5267)
      (2238.7939 7199.0687) (2240.4733 7198.2137) (2239.8779 7196.4122) (2237.542 7193.4046) (2234.458 7189.3435)
      (2231.8321 7184.8397) (2230.6565 7180.7786) (2231.4809 7178.0458) (2234.2137 7177.2214) (2238.2748 7178.3969)
      (2242.7786 7181.0229) (2246.8397 7184.1069) (2249.8473 7186.4427) (2251.6489 7187.0382) (2252.5038 7185.3588)
      (2252.9618 7181.5725) (2253.6641 7176.5191) (2254.9771 7171.4809) (2257.0229 7167.771) (2259.542 7166.4122)
      (2262.0611 7167.771) (2264.1069 7171.4809) (2265.4351 7176.5191) (2266.1221 7181.5725) (2266.5802 7185.3588)
      (2267.4351 7187.0382) (2269.2366 7186.4427) (2272.2443 7184.1069) (2276.3053 7181.0229) (2280.8092 7178.3969)
      (2284.8702 7177.2214) (2287.6031 7178.0458) (2288.4275 7180.7786) (2287.2519 7184.8397) (2284.626 7189.3435)
      (2281.542 7193.4046) (2279.2061 7196.4122) (2278.6107 7198.2137) (2280.2901 7199.0687) (2284.0763 7199.5267)
      (2289.1298 7200.2137) (2294.1679 7201.542) (2297.8779 7203.5878) (2299.2366 7206.1069) (2297.8779 7208.626)
      (2294.1679 7210.6718) (2289.1298 7211.9847) (2284.0763 7212.687) (2280.2901 7213.145) (2278.6107 7214.0)
      (2279.2061 7215.8015) (2281.542 7218.8092) (2284.626 7222.8702) (2287.2519 7227.374) (2288.4275 7231.4351)
      (2287.6031 7234.1679) (2284.8702 7234.9924) (2280.8092 7233.8168) (2276.3053 7231.1908) (2272.2443 7228.1069)
      (2269.2366 7225.771) (2267.4351 7225.1756) (2266.5802 7226.855) (2266.1221 7230.6412) (2265.4351 7235.6947)
      (2264.1069 7240.7328) (2262.0611 7244.4427) (2259.542 7245.8015) (2257.0229 7244.4427) (2254.9771 7240.7328)
      (2253.6641 7235.6947) (2252.9618 7230.6412) (2252.5038 7226.855) (2251.6489 7225.1756) (2249.8473 7225.771)
      (2246.8397 7228.1069) (2242.7786 7231.1908) (2238.2748 7233.8168) (2234.2137 7234.9924) (2231.4809 7234.1679)
      (2230.6565 7231.4351) (2231.8321 7227.374) (2234.458 7222.8702) (2237.542 7218.8092) (2239.8779 7215.8015)
      (2240.4733 7214.0) (2238.7939 7213.145) (2235.0076 7212.687) (2229.9542 7211.9847) (2224.916 7210.6718)
      (2221.2061 7208.626)
    ))
    ; P2757 -- see feature_dimensions_mm.csv
    ("06_ORNAMENT" 1 (
      (2221.374 2198.4733) (2223.2366 2186.6718) (2228.6565 2176.0458) (2237.1145 2167.5878) (2247.7405 2162.1679)
      (2259.542 2160.3053) (2271.3435 2162.1679) (2281.9695 2167.5878) (2290.4275 2176.0458) (2295.8473 2186.6718)
      (2297.7099 2198.4733) (2295.8473 2210.2748) (2290.4275 2220.9008) (2281.9695 2229.3588) (2271.3435 2234.7786)
      (2259.542 2236.6412) (2247.7405 2234.7786) (2237.1145 2229.3588) (2228.6565 2220.9008) (2223.2366 2210.2748)
    ))
    ; P2758 -- see feature_dimensions_mm.csv
    ("06_ORNAMENT" 1 (
      (2221.374 1282.4427) (2223.2366 1270.6412) (2228.6565 1260.0153) (2237.1145 1251.5573) (2247.7405 1246.1374)
      (2259.542 1244.2748) (2271.3435 1246.1374) (2281.9695 1251.5573) (2290.4275 1260.0153) (2295.8473 1270.6412)
      (2297.7099 1282.4427) (2295.8473 1294.2443) (2290.4275 1304.8702) (2281.9695 1313.3282) (2271.3435 1318.7481)
      (2259.542 1320.6107) (2247.7405 1318.7481) (2237.1145 1313.3282) (2228.6565 1304.8702) (2223.2366 1294.2443)
    ))
    ; P2759 -- see feature_dimensions_mm.csv
    ("06_ORNAMENT" 1 (
      (2250.4122 7374.0458) (2251.1145 7370.5496) (2253.084 7367.5878) (2256.0458 7365.6183) (2259.542 7364.916)
      (2263.0382 7365.6183) (2266.0 7367.5878) (2267.9695 7370.5496) (2268.6718 7374.0458) (2267.9695 7377.542)
      (2266.0 7380.5038) (2263.0382 7382.4733) (2259.542 7383.1756) (2256.0458 7382.4733) (2253.084 7380.5038)
      (2251.1145 7377.542)
    ))
    ; P2760 -- see feature_dimensions_mm.csv
    ("06_ORNAMENT" 1 (
      (2250.4122 7206.1069) (2251.1145 7202.6107) (2253.084 7199.6489) (2256.0458 7197.6794) (2259.542 7196.9771)
      (2263.0382 7197.6794) (2266.0 7199.6489) (2267.9695 7202.6107) (2268.6718 7206.1069) (2267.9695 7209.6031)
      (2266.0 7212.5649) (2263.0382 7214.5344) (2259.542 7215.2366) (2256.0458 7214.5344) (2253.084 7212.5649)
      (2251.1145 7209.6031)
    ))
    ; P2761 -- see feature_dimensions_mm.csv
    ("06_ORNAMENT" 1 (
      (2262.5954 6135.8779) (2265.2672 6137.1908) (2270.2901 6138.3664) (2277.0534 6139.3282) (2284.9313 6139.9847)
      (2293.2977 6140.2137) (2301.5573 6139.9237) (2309.084 6139.0229) (2315.2672 6137.4046) (2320.626 6134.9466)
      (2325.9695 6131.6947) (2331.1145 6127.7863) (2335.8779 6123.374) (2340.0763 6118.626) (2343.4962 6113.6794)
      (2345.9847 6108.687) (2347.3282 6103.8168) (2347.771 6098.8092) (2347.6031 6093.4198) (2346.6718 6087.7863)
      (2344.9008 6082.0611) (2342.1221 6076.3817) (2338.2595 6070.9008) (2336.8244 6069.4504) (2334.916 6070.1985)
      (2299.1756 6082.3664) (2269.1908 6091.2977) (2272.3817 6092.7023) (2278.1221 6096.1679) (2283.3435 6100.1832)
      (2287.8473 6104.4733) (2291.3893 6108.7328) (2293.7252 6112.6718) (2294.6565 6116.0305) (2293.2519 6119.0076)
      (2289.3282 6121.9542) (2283.771 6124.8397) (2277.4809 6127.5725) (2271.3282 6130.1069) (2266.2137 6132.3817)
      (2263.0076 6134.3206)
    ))
    ; P2762 -- see feature_dimensions_mm.csv
    ("06_ORNAMENT" 1 (
      (2269.313 3007.6336) (2270.0305 3006.3206) (2271.9542 3005.2519) (2274.5954 3004.5496) (2277.2366 3004.1985)
      (2279.2214 3003.9542) (2280.1069 3003.4962) (2279.8015 3002.5649) (2278.5649 3000.9924) (2276.9618 2998.8702)
      (2275.5878 2996.5038) (2274.9618 2994.3817) (2275.3893 2992.9466) (2276.8244 2992.5191) (2278.9466 2993.145)
      (2281.313 2994.5191) (2283.4351 2996.1221) (2285.0076 2997.3588) (2285.9389 2997.6641) (2286.3969 2996.7786)
      (2286.6412 2994.7939) (2286.9924 2992.1527) (2287.6947 2989.5115) (2288.7634 2987.5878) (2290.0763 2986.8702)
      (2291.3893 2987.5878) (2292.458 2989.5115) (2293.1603 2992.1527) (2293.5115 2994.7939) (2293.7557 2996.7786)
      (2294.2137 2997.6641) (2295.145 2997.3588) (2296.7176 2996.1221) (2298.8397 2994.5191) (2301.2061 2993.145)
      (2303.3282 2992.5191) (2304.7634 2992.9466) (2305.1908 2994.3817) (2304.5649 2996.5038) (2303.1908 2998.8702)
      (2301.5878 3000.9924) (2300.3511 3002.5649) (2300.0458 3003.4962) (2300.9313 3003.9542) (2302.916 3004.1985)
      (2305.5573 3004.5496) (2308.1985 3005.2519) (2310.1221 3006.3206) (2310.8397 3007.6336) (2310.1221 3008.9466)
      (2308.1985 3010.0153) (2305.5573 3010.7176) (2302.916 3011.0687) (2300.9313 3011.313) (2300.0458 3011.771)
      (2300.3511 3012.7023) (2301.5878 3014.2748) (2303.1908 3016.3969) (2304.5649 3018.7634) (2305.1908 3020.8855)
      (2304.7634 3022.3206) (2303.3282 3022.7481) (2301.2061 3022.1221) (2298.8397 3020.7481) (2296.7176 3019.145)
      (2295.145 3017.9084) (2294.2137 3017.6031) (2293.7557 3018.4885) (2293.5115 3020.4733) (2293.1603 3023.1145)
      (2292.458 3025.7557) (2291.3893 3027.6794) (2290.0763 3028.3969) (2288.7634 3027.6794) (2287.6947 3025.7557)
      (2286.9924 3023.1145) (2286.6412 3020.4733) (2286.3969 3018.4885) (2285.9389 3017.6031) (2285.0076 3017.9084)
      (2283.4351 3019.145) (2281.313 3020.7481) (2278.9466 3022.1221) (2276.8244 3022.7481) (2275.3893 3022.3206)
      (2274.9618 3020.8855) (2275.5878 3018.7634) (2276.9618 3016.3969) (2278.5649 3014.2748) (2279.8015 3012.7023)
      (2280.1069 3011.771) (2279.2214 3011.313) (2277.2366 3011.0687) (2274.5954 3010.7176) (2271.9542 3010.0153)
      (2270.0305 3008.9466)
    ))
    ; P2763 -- see feature_dimensions_mm.csv
    ("06_ORNAMENT" 1 (
      (2269.313 2900.7634) (2270.0305 2899.4504) (2271.9542 2898.3817) (2274.5954 2897.6794) (2277.2366 2897.3282)
      (2279.2214 2897.084) (2280.1069 2896.626) (2279.8015 2895.6947) (2278.5649 2894.1221) (2276.9618 2892.0)
      (2275.5878 2889.6336) (2274.9618 2887.5115) (2275.3893 2886.0763) (2276.8244 2885.6489) (2278.9466 2886.2748)
      (2281.313 2887.6489) (2283.4351 2889.2519) (2285.0076 2890.4885) (2285.9389 2890.7939) (2286.3969 2889.9084)
      (2286.6412 2887.9237) (2286.9924 2885.2824) (2287.6947 2882.6412) (2288.7634 2880.7176) (2290.0763 2880.0)
      (2291.3893 2880.7176) (2292.458 2882.6412) (2293.1603 2885.2824) (2293.5115 2887.9237) (2293.7557 2889.9084)
      (2294.2137 2890.7939) (2295.145 2890.4885) (2296.7176 2889.2519) (2298.8397 2887.6489) (2301.2061 2886.2748)
      (2303.3282 2885.6489) (2304.7634 2886.0763) (2305.1908 2887.5115) (2304.5649 2889.6336) (2303.1908 2892.0)
      (2301.5878 2894.1221) (2300.3511 2895.6947) (2300.0458 2896.626) (2300.9313 2897.084) (2302.916 2897.3282)
      (2305.5573 2897.6794) (2308.1985 2898.3817) (2310.1221 2899.4504) (2310.8397 2900.7634) (2310.1221 2902.0763)
      (2308.1985 2903.145) (2305.5573 2903.8473) (2302.916 2904.1985) (2300.9313 2904.4427) (2300.0458 2904.9008)
      (2300.3511 2905.8321) (2301.5878 2907.4046) (2303.1908 2909.5267) (2304.5649 2911.8931) (2305.1908 2914.0153)
      (2304.7634 2915.4504) (2303.3282 2915.8779) (2301.2061 2915.2519) (2298.8397 2913.8779) (2296.7176 2912.2748)
      (2295.145 2911.0382) (2294.2137 2910.7328) (2293.7557 2911.6183) (2293.5115 2913.6031) (2293.1603 2916.2443)
      (2292.458 2918.8855) (2291.3893 2920.8092) (2290.0763 2921.5267) (2288.7634 2920.8092) (2287.6947 2918.8855)
      (2286.9924 2916.2443) (2286.6412 2913.6031) (2286.3969 2911.6183) (2285.9389 2910.7328) (2285.0076 2911.0382)
      (2283.4351 2912.2748) (2281.313 2913.8779) (2278.9466 2915.2519) (2276.8244 2915.8779) (2275.3893 2915.4504)
      (2274.9618 2914.0153) (2275.5878 2911.8931) (2276.9618 2909.5267) (2278.5649 2907.4046) (2279.8015 2905.8321)
      (2280.1069 2904.9008) (2279.2214 2904.4427) (2277.2366 2904.1985) (2274.5954 2903.8473) (2271.9542 2903.145)
      (2270.0305 2902.0763)
    ))
    ; P2764 -- see feature_dimensions_mm.csv
    ("06_ORNAMENT" 1 (
      (2280.1527 5275.0687) (2281.374 5268.9313) (2284.855 5263.7252) (2290.0458 5260.2595) (2296.1832 5259.0382)
      (2302.3206 5260.2595) (2307.5115 5263.7252) (2310.9924 5268.9313) (2312.2137 5275.0687) (2310.9924 5281.2061)
      (2307.5115 5286.3969) (2302.3206 5289.8779) (2296.1832 5291.0992) (2290.0458 5289.8779) (2284.855 5286.3969)
      (2281.374 5281.2061)
    ))
    ; P2765 -- see feature_dimensions_mm.csv
    ("06_ORNAMENT" 1 (
      (2280.1527 5198.7328) (2281.374 5192.5954) (2284.855 5187.3893) (2290.0458 5183.9237) (2296.1832 5182.7023)
      (2302.3206 5183.9237) (2307.5115 5187.3893) (2310.9924 5192.5954) (2312.2137 5198.7328) (2310.9924 5204.8702)
      (2307.5115 5210.0611) (2302.3206 5213.542) (2296.1832 5214.7634) (2290.0458 5213.542) (2284.855 5210.0611)
      (2281.374 5204.8702)
    ))
    ; P2766 -- see feature_dimensions_mm.csv
    ("06_ORNAMENT" 1 (
      (2280.1527 5122.3969) (2281.374 5116.2595) (2284.855 5111.0534) (2290.0458 5107.5878) (2296.1832 5106.3664)
      (2302.3206 5107.5878) (2307.5115 5111.0534) (2310.9924 5116.2595) (2312.2137 5122.3969) (2310.9924 5128.5344)
      (2307.5115 5133.7252) (2302.3206 5137.2061) (2296.1832 5138.4275) (2290.0458 5137.2061) (2284.855 5133.7252)
      (2281.374 5128.5344)
    ))
    ; P2767 -- see feature_dimensions_mm.csv
    ("06_ORNAMENT" 1 (
      (2280.1527 5046.0611) (2281.374 5039.9237) (2284.855 5034.7176) (2290.0458 5031.2519) (2296.1832 5030.0305)
      (2302.3206 5031.2519) (2307.5115 5034.7176) (2310.9924 5039.9237) (2312.2137 5046.0611) (2310.9924 5052.1985)
      (2307.5115 5057.3893) (2302.3206 5060.8702) (2296.1832 5062.0916) (2290.0458 5060.8702) (2284.855 5057.3893)
      (2281.374 5052.1985)
    ))
    ; P2768 -- see feature_dimensions_mm.csv
    ("06_ORNAMENT" 1 (
      (2280.1527 4969.7252) (2281.374 4963.5878) (2284.855 4958.3817) (2290.0458 4954.916) (2296.1832 4953.6947)
      (2302.3206 4954.916) (2307.5115 4958.3817) (2310.9924 4963.5878) (2312.2137 4969.7252) (2310.9924 4975.8626)
      (2307.5115 4981.0534) (2302.3206 4984.5344) (2296.1832 4985.7557) (2290.0458 4984.5344) (2284.855 4981.0534)
      (2281.374 4975.8626)
    ))
    ; P2769 -- see feature_dimensions_mm.csv
    ("06_ORNAMENT" 1 (
      (2280.1527 4893.3893) (2281.374 4887.2519) (2284.855 4882.0458) (2290.0458 4878.5802) (2296.1832 4877.3588)
      (2302.3206 4878.5802) (2307.5115 4882.0458) (2310.9924 4887.2519) (2312.2137 4893.3893) (2310.9924 4899.5267)
      (2307.5115 4904.7176) (2302.3206 4908.1985) (2296.1832 4909.4198) (2290.0458 4908.1985) (2284.855 4904.7176)
      (2281.374 4899.5267)
    ))
    ; P2770 -- see feature_dimensions_mm.csv
    ("06_ORNAMENT" 1 (
      (2280.1527 4817.0534) (2281.374 4810.916) (2284.855 4805.7099) (2290.0458 4802.2443) (2296.1832 4801.0229)
      (2302.3206 4802.2443) (2307.5115 4805.7099) (2310.9924 4810.916) (2312.2137 4817.0534) (2310.9924 4823.1908)
      (2307.5115 4828.3817) (2302.3206 4831.8626) (2296.1832 4833.084) (2290.0458 4831.8626) (2284.855 4828.3817)
      (2281.374 4823.1908)
    ))
    ; P2771 -- see feature_dimensions_mm.csv
    ("06_ORNAMENT" 1 (
      (2280.1527 4664.3817) (2281.374 4658.2443) (2284.855 4653.0382) (2290.0458 4649.5725) (2296.1832 4648.3511)
      (2302.3206 4649.5725) (2307.5115 4653.0382) (2310.9924 4658.2443) (2312.2137 4664.3817) (2310.9924 4670.5191)
      (2307.5115 4675.7099) (2302.3206 4679.1908) (2296.1832 4680.4122) (2290.0458 4679.1908) (2284.855 4675.7099)
      (2281.374 4670.5191)
    ))
    ; P2772 -- see feature_dimensions_mm.csv
    ("06_ORNAMENT" 1 (
      (2280.1527 4588.0458) (2281.374 4581.9084) (2284.855 4576.7023) (2290.0458 4573.2366) (2296.1832 4572.0153)
      (2302.3206 4573.2366) (2307.5115 4576.7023) (2310.9924 4581.9084) (2312.2137 4588.0458) (2310.9924 4594.1832)
      (2307.5115 4599.374) (2302.3206 4602.855) (2296.1832 4604.0763) (2290.0458 4602.855) (2284.855 4599.374)
      (2281.374 4594.1832)
    ))
    ; P2773 -- see feature_dimensions_mm.csv
    ("06_ORNAMENT" 1 (
      (2280.1527 4511.7099) (2281.374 4505.5725) (2284.855 4500.3664) (2290.0458 4496.9008) (2296.1832 4495.6794)
      (2302.3206 4496.9008) (2307.5115 4500.3664) (2310.9924 4505.5725) (2312.2137 4511.7099) (2310.9924 4517.8473)
      (2307.5115 4523.0382) (2302.3206 4526.5191) (2296.1832 4527.7405) (2290.0458 4526.5191) (2284.855 4523.0382)
      (2281.374 4517.8473)
    ))
    ; P2774 -- see feature_dimensions_mm.csv
    ("06_ORNAMENT" 1 (
      (2280.1527 4359.0382) (2281.374 4352.9008) (2284.855 4347.6947) (2290.0458 4344.229) (2296.1832 4343.0076)
      (2302.3206 4344.229) (2307.5115 4347.6947) (2310.9924 4352.9008) (2312.2137 4359.0382) (2310.9924 4365.1756)
      (2307.5115 4370.3664) (2302.3206 4373.8473) (2296.1832 4375.0687) (2290.0458 4373.8473) (2284.855 4370.3664)
      (2281.374 4365.1756)
    ))
    ; P2775 -- see feature_dimensions_mm.csv
    ("06_ORNAMENT" 1 (
      (2280.1527 4282.7023) (2281.374 4276.5649) (2284.855 4271.3588) (2290.0458 4267.8931) (2296.1832 4266.6718)
      (2302.3206 4267.8931) (2307.5115 4271.3588) (2310.9924 4276.5649) (2312.2137 4282.7023) (2310.9924 4288.8397)
      (2307.5115 4294.0305) (2302.3206 4297.5115) (2296.1832 4298.7328) (2290.0458 4297.5115) (2284.855 4294.0305)
      (2281.374 4288.8397)
    ))
    ; P2776 -- see feature_dimensions_mm.csv
    ("06_ORNAMENT" 1 (
      (2280.1527 4206.3664) (2281.374 4200.229) (2284.855 4195.0229) (2290.0458 4191.5573) (2296.1832 4190.3359)
      (2302.3206 4191.5573) (2307.5115 4195.0229) (2310.9924 4200.229) (2312.2137 4206.3664) (2310.9924 4212.5038)
      (2307.5115 4217.6947) (2302.3206 4221.1756) (2296.1832 4222.3969) (2290.0458 4221.1756) (2284.855 4217.6947)
      (2281.374 4212.5038)
    ))
    ; P2777 -- see feature_dimensions_mm.csv
    ("06_ORNAMENT" 1 (
      (2280.1527 4053.6947) (2281.374 4047.5573) (2284.855 4042.3511) (2290.0458 4038.8855) (2296.1832 4037.6641)
      (2302.3206 4038.8855) (2307.5115 4042.3511) (2310.9924 4047.5573) (2312.2137 4053.6947) (2310.9924 4059.8321)
      (2307.5115 4065.0229) (2302.3206 4068.5038) (2296.1832 4069.7252) (2290.0458 4068.5038) (2284.855 4065.0229)
      (2281.374 4059.8321)
    ))
    ; P2778 -- see feature_dimensions_mm.csv
    ("06_ORNAMENT" 1 (
      (2280.1527 3977.3588) (2281.374 3971.2214) (2284.855 3966.0153) (2290.0458 3962.5496) (2296.1832 3961.3282)
      (2302.3206 3962.5496) (2307.5115 3966.0153) (2310.9924 3971.2214) (2312.2137 3977.3588) (2310.9924 3983.4962)
      (2307.5115 3988.687) (2302.3206 3992.1679) (2296.1832 3993.3893) (2290.0458 3992.1679) (2284.855 3988.687)
      (2281.374 3983.4962)
    ))
    ; P2779 -- see feature_dimensions_mm.csv
    ("06_ORNAMENT" 1 (
      (2280.1527 3901.0229) (2281.374 3894.8855) (2284.855 3889.6794) (2290.0458 3886.2137) (2296.1832 3884.9924)
      (2302.3206 3886.2137) (2307.5115 3889.6794) (2310.9924 3894.8855) (2312.2137 3901.0229) (2310.9924 3907.1603)
      (2307.5115 3912.3511) (2302.3206 3915.8321) (2296.1832 3917.0534) (2290.0458 3915.8321) (2284.855 3912.3511)
      (2281.374 3907.1603)
    ))
    ; P2780 -- see feature_dimensions_mm.csv
    ("06_ORNAMENT" 1 (
      (2283.9695 3007.6336) (2284.4275 3005.2977) (2285.7557 3003.313) (2287.7405 3001.9847) (2290.0763 3001.5267)
      (2292.4122 3001.9847) (2294.3969 3003.313) (2295.7252 3005.2977) (2296.1832 3007.6336) (2295.7252 3009.9695)
      (2294.3969 3011.9542) (2292.4122 3013.2824) (2290.0763 3013.7405) (2287.7405 3013.2824) (2285.7557 3011.9542)
      (2284.4275 3009.9695)
    ))
    ; P2781 -- see feature_dimensions_mm.csv
    ("06_ORNAMENT" 1 (
      (2283.9695 2900.7634) (2284.4275 2898.4275) (2285.7557 2896.4427) (2287.7405 2895.1145) (2290.0763 2894.6565)
      (2292.4122 2895.1145) (2294.3969 2896.4427) (2295.7252 2898.4275) (2296.1832 2900.7634) (2295.7252 2903.0992)
      (2294.3969 2905.084) (2292.4122 2906.4122) (2290.0763 2906.8702) (2287.7405 2906.4122) (2285.7557 2905.084)
      (2284.4275 2903.0992)
    ))
    ; P2782 -- see feature_dimensions_mm.csv
    ("06_ORNAMENT" 1 (
      (2319.5878 5312.9771) (2321.0992 5307.313) (2325.2519 5303.1603) (2330.916 5301.6336) (2336.5802 5303.1603)
      (2340.7328 5307.313) (2342.2595 5312.9771) (2340.7328 5318.6412) (2336.5802 5322.7939) (2330.916 5324.3053)
      (2325.2519 5322.7939) (2321.0992 5318.6412)
    ))
    ; P2783 -- see feature_dimensions_mm.csv
    ("06_ORNAMENT" 1 (
      (2319.5878 4717.5573) (2321.0992 4711.8931) (2325.2519 4707.7405) (2330.916 4706.2137) (2336.5802 4707.7405)
      (2340.7328 4711.8931) (2342.2595 4717.5573) (2340.7328 4723.2214) (2336.5802 4727.374) (2330.916 4728.8855)
      (2325.2519 4727.374) (2321.0992 4723.2214)
    ))
    ; P2784 -- see feature_dimensions_mm.csv
    ("06_ORNAMENT" 1 (
      (2319.5878 4122.1374) (2321.0992 4116.4733) (2325.2519 4112.3206) (2330.916 4110.7939) (2336.5802 4112.3206)
      (2340.7328 4116.4733) (2342.2595 4122.1374) (2340.7328 4127.8015) (2336.5802 4131.9542) (2330.916 4133.4656)
      (2325.2519 4131.9542) (2321.0992 4127.8015)
    ))
    ; P2785 -- see feature_dimensions_mm.csv
    ("06_ORNAMENT" 1 (
      (2331.9847 1861.9237) (2333.9847 1848.2595) (2338.6565 1836.458) (2345.9084 1826.8244) (2355.542 1819.5725)
      (2367.3435 1814.9008) (2381.0076 1812.9008) (2396.1832 1813.6489) (2412.5344 1817.1145) (2429.6183 1823.2061)
      (2447.0534 1831.771) (2464.3817 1842.626) (2481.1756 1855.4656) (2497.0382 1870.0) (2511.5725 1885.8626)
      (2524.4275 1902.6718) (2535.2672 1920.0) (2543.8473 1937.4198) (2549.9389 1954.5191) (2553.4046 1970.855)
      (2554.1374 1986.0458) (2552.1527 1999.7099) (2547.4809 2011.4962) (2540.229 2021.145) (2530.5802 2028.3817)
      (2518.7939 2033.0687) (2505.1298 2035.0534) (2489.9389 2034.3053) (2473.6031 2030.855) (2456.5038 2024.7634)
      (2439.084 2016.1832) (2421.7557 2005.3435) (2404.9466 1992.4885) (2389.084 1977.9542) (2374.5496 1962.0916)
      (2361.7099 1945.2977) (2350.855 1927.9695) (2342.2901 1910.5344) (2336.1985 1893.4504) (2332.7328 1877.0992)
    ))
    ; P2786 -- see feature_dimensions_mm.csv
    ("06_ORNAMENT" 1 (
      (2331.9847 1618.9924) (2332.7328 1603.8168) (2336.1985 1587.4656) (2342.2901 1570.3817) (2350.855 1552.9466)
      (2361.7099 1535.6183) (2374.5496 1518.8244) (2389.084 1502.9618) (2404.9466 1488.4275) (2421.7557 1475.5725)
      (2439.084 1464.7328) (2456.5038 1456.1527) (2473.6031 1450.0611) (2489.9389 1446.5954) (2505.1298 1445.8626)
      (2518.7939 1447.8473) (2530.5802 1452.5191) (2540.229 1459.771) (2547.4809 1469.4198) (2552.1527 1481.2061)
      (2554.1374 1494.8702) (2553.4046 1510.0611) (2549.9389 1526.3969) (2543.8473 1543.4962) (2535.2672 1560.916)
      (2524.4275 1578.2443) (2511.5725 1595.0534) (2497.0382 1610.916) (2481.1756 1625.4504) (2464.3817 1638.2901)
      (2447.0534 1649.145) (2429.6183 1657.7099) (2412.5344 1663.8015) (2396.1832 1667.2672) (2381.0076 1668.0153)
      (2367.3435 1666.0153) (2355.542 1661.3435) (2345.9084 1654.0916) (2338.6565 1644.458) (2333.9847 1632.6565)
    ))
    ; P2787 -- see feature_dimensions_mm.csv
    ("06_ORNAMENT" 1 (
      (2339.7099 5211.7557) (2341.2366 5206.0916) (2345.3893 5201.9389) (2351.0534 5200.4275) (2356.7176 5201.9389)
      (2360.8702 5206.0916) (2362.3817 5211.7557) (2360.8702 5217.4198) (2356.7176 5221.5725) (2351.0534 5223.0992)
      (2345.3893 5221.5725) (2341.2366 5217.4198)
    ))
    ; P2788 -- see feature_dimensions_mm.csv
    ("06_ORNAMENT" 1 (
      (2339.7099 4818.7786) (2341.2366 4813.1145) (2345.3893 4808.9618) (2351.0534 4807.4351) (2356.7176 4808.9618)
      (2360.8702 4813.1145) (2362.3817 4818.7786) (2360.8702 4824.4427) (2356.7176 4828.5954) (2351.0534 4830.1069)
      (2345.3893 4828.5954) (2341.2366 4824.4427)
    ))
    ; P2789 -- see feature_dimensions_mm.csv
    ("06_ORNAMENT" 1 (
      (2339.7099 4616.3359) (2341.2366 4610.6718) (2345.3893 4606.5191) (2351.0534 4605.0076) (2356.7176 4606.5191)
      (2360.8702 4610.6718) (2362.3817 4616.3359) (2360.8702 4622.0) (2356.7176 4626.1527) (2351.0534 4627.6794)
      (2345.3893 4626.1527) (2341.2366 4622.0)
    ))
    ; P2790 -- see feature_dimensions_mm.csv
    ("06_ORNAMENT" 1 (
      (2339.7099 4223.3588) (2341.2366 4217.6947) (2345.3893 4213.542) (2351.0534 4212.0153) (2356.7176 4213.542)
      (2360.8702 4217.6947) (2362.3817 4223.3588) (2360.8702 4229.0229) (2356.7176 4233.1756) (2351.0534 4234.687)
      (2345.3893 4233.1756) (2341.2366 4229.0229)
    ))
    ; P2791 -- see feature_dimensions_mm.csv
    ("06_ORNAMENT" 1 (
      (2339.7099 4020.916) (2341.2366 4015.2519) (2345.3893 4011.0992) (2351.0534 4009.5878) (2356.7176 4011.0992)
      (2360.8702 4015.2519) (2362.3817 4020.916) (2360.8702 4026.5802) (2356.7176 4030.7328) (2351.0534 4032.2595)
      (2345.3893 4030.7328) (2341.2366 4026.5802)
    ))
    ; P2792 -- see feature_dimensions_mm.csv
    ("06_ORNAMENT" 1 (
      (2346.0305 4122.1374) (2346.3969 4118.3969) (2347.5115 4114.7481) (2348.9924 4111.9084) (2349.4962 4100.626)
      (2352.3053 4079.2672) (2356.9618 4058.2443) (2363.4351 4037.7099) (2371.6794 4017.8015) (2381.6183 3998.7023)
      (2393.1908 3980.5344) (2406.3053 3963.4504) (2413.9389 3955.1298) (2414.8855 3952.0611) (2416.687 3948.7023)
      (2419.0687 3945.7863) (2421.9847 3943.4046) (2425.3435 3941.6031) (2428.4122 3940.6565) (2436.7328 3933.0229)
      (2453.8168 3919.9084) (2471.9847 3908.3359) (2491.084 3898.3969) (2510.9924 3890.1527) (2531.5267 3883.6794)
      (2552.5496 3879.0229) (2573.9084 3876.2137) (2585.1908 3875.7099) (2588.0305 3874.229) (2591.6794 3873.1145)
      (2595.4198 3872.7481) (2599.1603 3873.1145) (2602.8092 3874.229) (2605.6489 3875.7099) (2616.9313 3876.2137)
      (2638.2901 3879.0229) (2659.313 3883.6794) (2679.8473 3890.1527) (2699.7557 3898.3969) (2718.855 3908.3359)
      (2737.0229 3919.9084) (2754.1069 3933.0229) (2762.4275 3940.6565) (2765.4962 3941.6031) (2768.855 3943.4046)
      (2771.771 3945.7863) (2774.1527 3948.7023) (2775.9542 3952.0611) (2776.9008 3955.1298) (2784.5344 3963.4504)
      (2797.6489 3980.5344) (2809.2214 3998.7023) (2819.1603 4017.8015) (2827.4046 4037.7099) (2833.8779 4058.2443)
      (2838.5344 4079.2672) (2841.3435 4100.626) (2841.8473 4111.9084) (2843.3282 4114.7481) (2844.4427 4118.3969)
      (2844.8092 4122.1374) (2844.4427 4125.8779) (2843.3282 4129.5267) (2841.8473 4132.3664) (2841.3435 4143.6489)
      (2838.5344 4165.0076) (2833.8779 4186.0305) (2827.4046 4206.5649) (2819.1603 4226.4733) (2809.2214 4245.5725)
      (2797.6489 4263.7405) (2784.5344 4280.8244) (2776.9008 4289.145) (2775.9542 4292.2137) (2774.1527 4295.5725)
      (2771.771 4298.4885) (2768.855 4300.8702) (2765.4962 4302.6718) (2762.4275 4303.6183) (2754.1069 4311.2519)
      (2737.0229 4324.3664) (2718.855 4335.9389) (2699.7557 4345.8779) (2679.8473 4354.1221) (2659.313 4360.5954)
      (2638.2901 4365.2519) (2616.9313 4368.0611) (2605.6489 4368.5649) (2602.8092 4370.0458) (2599.1603 4371.1603)
      (2595.4198 4371.5267) (2591.6794 4371.1603) (2588.0305 4370.0458) (2585.1908 4368.5649) (2573.9084 4368.0611)
      (2552.5496 4365.2519) (2531.5267 4360.5954) (2510.9924 4354.1221) (2491.084 4345.8779) (2471.9847 4335.9389)
      (2453.8168 4324.3664) (2436.7328 4311.2519) (2428.4122 4303.6183) (2425.3435 4302.6718) (2421.9847 4300.8702)
      (2419.0687 4298.4885) (2416.687 4295.5725) (2414.8855 4292.2137) (2413.9389 4289.145) (2406.3053 4280.8244)
      (2393.1908 4263.7405) (2381.6183 4245.5725) (2371.6794 4226.4733) (2363.4351 4206.5649) (2356.9618 4186.0305)
      (2352.3053 4165.0076) (2349.4962 4143.6489) (2348.9924 4132.3664) (2347.5115 4129.5267) (2346.3969 4125.8779)
    ))
    ; P2793 -- see feature_dimensions_mm.csv
    ("06_ORNAMENT" 1 (
      (2360.2443 2099.7557) (2361.5878 2088.3664) (2364.3664 2077.9542) (2368.5191 2068.7786) (2373.9542 2061.0687)
      (2380.5344 2055.0076) (2388.0763 2050.7634) (2396.4122 2048.4275) (2405.3435 2048.0611) (2414.626 2049.6794)
      (2424.0611 2053.2214) (2433.3893 2058.6107) (2442.3969 2065.7252) (2450.8702 2074.3817) (2458.5802 2084.3664)
      (2465.3435 2095.4351) (2470.9924 2107.313) (2475.3893 2119.7099) (2476.6565 2124.9618) (2480.4427 2124.2901)
      (2485.7863 2123.6031) (2489.6031 2122.8702) (2491.5878 2121.5267) (2491.7557 2119.145) (2490.4885 2115.4656)
      (2488.4122 2110.5038) (2486.2595 2104.5802) (2484.7786 2098.2901) (2484.5191 2092.3664) (2485.771 2087.5573)
      (2488.5496 2084.5191) (2492.5649 2083.6336) (2497.3588 2084.9466) (2502.3664 2088.1374) (2507.0687 2092.5802)
      (2511.1298 2097.3893) (2514.3817 2101.6641) (2516.9313 2104.6107) (2519.084 2105.6489) (2521.2366 2104.6107)
      (2523.7863 2101.6641) (2527.0382 2097.3893) (2531.0992 2092.5802) (2535.8015 2088.1374) (2540.8092 2084.9466)
      (2545.6031 2083.6336) (2549.6183 2084.5191) (2552.3969 2087.5573) (2553.6489 2092.3664) (2553.3893 2098.2901)
      (2551.9084 2104.5802) (2549.7557 2110.5038) (2547.6794 2115.4656) (2546.4122 2119.145) (2546.5802 2121.5267)
      (2548.5649 2122.8702) (2552.3817 2123.6031) (2557.7252 2124.2901) (2563.9084 2125.3893) (2570.1069 2127.2519)
      (2575.374 2130.0) (2578.916 2133.4809) (2580.1527 2137.4046) (2578.916 2141.3282) (2575.374 2144.8092)
      (2570.1069 2147.5573) (2563.9084 2149.4198) (2557.7252 2150.5191) (2552.3817 2151.2061) (2548.5649 2151.9389)
      (2546.5802 2153.2824) (2546.4122 2155.6641) (2547.6794 2159.3435) (2549.7557 2164.3053) (2551.9084 2170.229)
      (2552.9313 2174.5954) (2538.3664 2185.8473) (2536.4885 2187.0992) (2535.8015 2186.6718) (2531.0992 2182.229)
      (2527.0382 2177.4198) (2523.7863 2173.145) (2521.2366 2170.1985) (2519.084 2169.1603) (2516.9313 2170.1985)
      (2514.3817 2173.145) (2511.1298 2177.4198) (2507.0687 2182.229) (2502.3664 2186.6718) (2497.3588 2189.8626)
      (2492.5649 2191.1756) (2488.5496 2190.2901) (2485.771 2187.2519) (2484.5191 2182.4427) (2484.7786 2176.5191)
      (2486.2595 2170.229) (2488.4122 2164.3053) (2490.4885 2159.3435) (2491.7557 2155.6641) (2491.5878 2153.2824)
      (2489.6031 2151.9389) (2485.7863 2151.2061) (2480.4427 2150.5191) (2480.1069 2150.458) (2480.1832 2156.9313)
      (2478.8397 2168.3359) (2476.0611 2178.7481) (2471.8931 2187.9237) (2466.458 2195.6336) (2459.8931 2201.6794)
      (2452.3511 2205.9237) (2444.0 2208.2595) (2435.084 2208.626) (2425.7863 2207.0229) (2416.3664 2203.4656)
      (2407.0229 2198.0763) (2398.0153 2190.9618) (2389.5573 2182.3053) (2381.8473 2172.3206) (2375.084 2161.2519)
      (2369.4351 2149.374) (2365.0382 2136.9771) (2361.9847 2124.3817) (2360.3817 2111.8626)
    ))
    ; P2794 -- see feature_dimensions_mm.csv
    ("06_ORNAMENT" 1 (
      (2360.2443 1381.145) (2360.3817 1369.0534) (2361.9847 1356.5344) (2365.0382 1343.9389) (2369.4351 1331.542)
      (2375.084 1319.6641) (2381.8473 1308.5954) (2389.5573 1298.6107) (2398.0153 1289.9542) (2407.0229 1282.8397)
      (2416.3664 1277.4504) (2425.7863 1273.8931) (2435.084 1272.2901) (2444.0 1272.6565) (2452.3511 1274.9924)
      (2459.8931 1279.2366) (2466.458 1285.2824) (2471.8931 1292.9924) (2476.0611 1302.1679) (2478.8397 1312.5802)
      (2480.1832 1323.9847) (2480.0458 1336.0916) (2478.4275 1348.5954) (2475.3893 1361.2061) (2475.1603 1361.8779)
      (2480.4427 1360.9313) (2485.7863 1360.2443) (2489.6031 1359.5115) (2491.5878 1358.1679) (2491.7557 1355.7863)
      (2490.4885 1352.1069) (2488.4122 1347.145) (2486.2595 1341.2214) (2484.7786 1334.9313) (2484.5191 1329.0076)
      (2485.771 1324.1985) (2488.5496 1321.1603) (2492.5649 1320.2748) (2497.3588 1321.5878) (2502.3664 1324.7786)
      (2507.0687 1329.2214) (2511.1298 1334.0305) (2514.3817 1338.3053) (2516.9313 1341.2519) (2519.084 1342.2901)
      (2521.2366 1341.2519) (2523.7863 1338.3053) (2527.0382 1334.0305) (2531.0992 1329.2214) (2535.8015 1324.7786)
      (2540.8092 1321.5878) (2545.6031 1320.2748) (2549.6183 1321.1603) (2552.3969 1324.1985) (2553.6489 1329.0076)
      (2553.3893 1334.9313) (2551.9084 1341.2214) (2549.7557 1347.145) (2547.6794 1352.1069) (2546.4122 1355.7863)
      (2546.5802 1358.1679) (2548.5649 1359.5115) (2552.3817 1360.2443) (2557.7252 1360.9313) (2563.9084 1362.0305)
      (2570.1069 1363.8931) (2575.374 1366.6412) (2578.916 1370.1221) (2580.1527 1374.0458) (2578.916 1377.9695)
      (2577.4962 1379.3588) (2583.4046 1378.4275) (2595.2061 1380.2901) (2605.8473 1385.7099) (2614.2901 1394.1527)
      (2619.7099 1404.7939) (2621.5725 1416.5954) (2619.7099 1428.3817) (2614.2901 1439.0229) (2605.8473 1447.4656)
      (2595.2061 1452.8855) (2583.4046 1454.7634) (2571.6183 1452.8855) (2560.9771 1447.4656) (2552.5344 1439.0229)
      (2547.1145 1428.3817) (2546.9771 1427.5115) (2545.6031 1427.8168) (2540.8092 1426.5038) (2535.8015 1423.313)
      (2531.0992 1418.8702) (2527.0382 1414.0611) (2523.7863 1409.7863) (2521.2366 1406.8397) (2519.084 1405.8015)
      (2516.9313 1406.8397) (2514.3817 1409.7863) (2511.1298 1414.0611) (2507.0687 1418.8702) (2502.3664 1423.313)
      (2497.3588 1426.5038) (2492.5649 1427.8168) (2488.5496 1426.9313) (2485.771 1423.8931) (2484.5191 1419.084)
      (2484.7786 1413.1603) (2486.2595 1406.8702) (2488.4122 1400.9466) (2490.4885 1395.9847) (2491.7557 1392.3053)
      (2491.5878 1389.9237) (2489.6031 1388.5802) (2485.7863 1387.8473) (2480.4427 1387.1603) (2474.2595 1386.0611)
      (2468.0611 1384.1985) (2466.3664 1383.313) (2465.3435 1385.4809) (2458.5802 1396.5496) (2450.8702 1406.5344)
      (2442.3969 1415.1908) (2433.3893 1422.3053) (2424.0611 1427.6947) (2414.626 1431.2366) (2405.3435 1432.855)
      (2396.4122 1432.4885) (2388.0763 1430.1527) (2380.5344 1425.9084) (2373.9542 1419.8473) (2368.5191 1412.1374)
      (2364.3664 1402.9618) (2361.5878 1392.5496)
    ))
    ; P2795 -- see feature_dimensions_mm.csv
    ("06_ORNAMENT" 1 (
      (2374.7328 5232.0) (2375.9695 5224.2137) (2379.542 5217.1908) (2385.1145 5211.6183) (2392.1374 5208.0458)
      (2399.9237 5206.8092) (2407.7099 5208.0458) (2414.7328 5211.6183) (2420.3053 5217.1908) (2423.8779 5224.2137)
      (2425.1145 5232.0) (2423.8779 5239.7863) (2420.3053 5246.8092) (2414.7328 5252.3817) (2407.7099 5255.9542)
      (2399.9237 5257.1908) (2392.1374 5255.9542) (2385.1145 5252.3817) (2379.542 5246.8092) (2375.9695 5239.7863)
    ))
    ; P2796 -- see feature_dimensions_mm.csv
    ("06_ORNAMENT" 1 (
      (2374.7328 4798.5344) (2375.9695 4790.7481) (2379.542 4783.7252) (2385.1145 4778.1527) (2392.1374 4774.5802)
      (2399.9237 4773.3435) (2407.7099 4774.5802) (2414.7328 4778.1527) (2420.3053 4783.7252) (2423.8779 4790.7481)
      (2425.1145 4798.5344) (2423.8779 4806.3206) (2420.3053 4813.3435) (2414.7328 4818.916) (2407.7099 4822.4885)
      (2399.9237 4823.7252) (2392.1374 4822.4885) (2385.1145 4818.916) (2379.542 4813.3435) (2375.9695 4806.3206)
    ))
    ; P2797 -- see feature_dimensions_mm.csv
    ("06_ORNAMENT" 1 (
      (2374.7328 4636.5802) (2375.9695 4628.7939) (2379.542 4621.771) (2385.1145 4616.1985) (2392.1374 4612.626)
      (2399.9237 4611.3893) (2407.7099 4612.626) (2414.7328 4616.1985) (2420.3053 4621.771) (2423.8779 4628.7939)
      (2425.1145 4636.5802) (2423.8779 4644.3664) (2420.3053 4651.3893) (2414.7328 4656.9618) (2407.7099 4660.5344)
      (2399.9237 4661.771) (2392.1374 4660.5344) (2385.1145 4656.9618) (2379.542 4651.3893) (2375.9695 4644.3664)
    ))
    ; P2798 -- see feature_dimensions_mm.csv
    ("06_ORNAMENT" 1 (
      (2374.7328 4203.1145) (2375.9695 4195.3282) (2379.542 4188.3053) (2385.1145 4182.7328) (2392.1374 4179.1603)
      (2399.9237 4177.9237) (2407.7099 4179.1603) (2414.7328 4182.7328) (2420.3053 4188.3053) (2423.8779 4195.3282)
      (2425.1145 4203.1145) (2423.8779 4210.9008) (2420.3053 4217.9237) (2414.7328 4223.4962) (2407.7099 4227.0687)
      (2399.9237 4228.3053) (2392.1374 4227.0687) (2385.1145 4223.4962) (2379.542 4217.9237) (2375.9695 4210.9008)
    ))
    ; P2799 -- see feature_dimensions_mm.csv
    ("06_ORNAMENT" 1 (
      (2374.7328 4041.1603) (2375.9695 4033.374) (2379.542 4026.3511) (2385.1145 4020.7786) (2392.1374 4017.2061)
      (2399.9237 4015.9695) (2407.7099 4017.2061) (2414.7328 4020.7786) (2420.3053 4026.3511) (2423.8779 4033.374)
      (2425.1145 4041.1603) (2423.8779 4048.9466) (2420.3053 4055.9695) (2414.7328 4061.542) (2407.7099 4065.1145)
      (2399.9237 4066.3511) (2392.1374 4065.1145) (2385.1145 4061.542) (2379.542 4055.9695) (2375.9695 4048.9466)
    ))
    ; P2800 -- see feature_dimensions_mm.csv
    ("06_ORNAMENT" 1 (
      (2381.6794 1740.458) (2383.374 1728.5191) (2388.3969 1716.8702) (2396.6565 1705.8015) (2407.9237 1695.5878)
      (2421.9237 1686.4733) (2438.3206 1678.7023) (2456.7023 1672.4427) (2476.626 1667.8626) (2497.5878 1665.0687)
      (2519.084 1664.1221) (2540.5802 1665.0687) (2561.542 1667.8626) (2581.4656 1672.4427) (2599.8473 1678.7023)
      (2616.2443 1686.4733) (2630.2443 1695.5878) (2641.5115 1705.8015) (2649.771 1716.8702) (2654.7939 1728.5191)
      (2656.4885 1740.458) (2654.7939 1752.3969) (2649.771 1764.0458) (2641.5115 1775.1145) (2630.2443 1785.3282)
      (2616.2443 1794.4427) (2599.8473 1802.2137) (2581.4656 1808.4733) (2561.542 1813.0534) (2540.5802 1815.8473)
      (2519.084 1816.7939) (2497.5878 1815.8473) (2476.626 1813.0534) (2456.7023 1808.4733) (2438.3206 1802.2137)
      (2421.9237 1794.4427) (2407.9237 1785.3282) (2396.6565 1775.1145) (2388.3969 1764.0458) (2383.374 1752.3969)
    ))
    ; P2801 -- see feature_dimensions_mm.csv
    ("06_ORNAMENT" 1 (
      (2397.0534 5125.9389) (2398.5649 5120.2748) (2402.7176 5116.1221) (2408.3817 5114.6107) (2414.0611 5116.1221)
      (2418.1985 5120.2748) (2419.7252 5125.9389) (2418.1985 5131.6183) (2414.0611 5135.7557) (2408.3817 5137.2824)
      (2402.7176 5135.7557) (2398.5649 5131.6183)
    ))
    ; P2802 -- see feature_dimensions_mm.csv
    ("06_ORNAMENT" 1 (
      (2397.0534 4904.5954) (2398.5649 4898.916) (2402.7176 4894.7786) (2408.3817 4893.2519) (2414.0611 4894.7786)
      (2418.1985 4898.916) (2419.7252 4904.5954) (2418.1985 4910.2595) (2414.0611 4914.4122) (2408.3817 4915.9237)
      (2402.7176 4914.4122) (2398.5649 4910.2595)
    ))
    ; P2803 -- see feature_dimensions_mm.csv
    ("06_ORNAMENT" 1 (
      (2397.0534 4530.5191) (2398.5649 4524.855) (2402.7176 4520.7023) (2408.3817 4519.1908) (2414.0611 4520.7023)
      (2418.1985 4524.855) (2419.7252 4530.5191) (2418.1985 4536.1985) (2414.0611 4540.3359) (2408.3817 4541.8626)
      (2402.7176 4540.3359) (2398.5649 4536.1985)
    ))
    ; P2804 -- see feature_dimensions_mm.csv
    ("06_ORNAMENT" 1 (
      (2397.0534 4309.1756) (2398.5649 4303.4962) (2402.7176 4299.3588) (2408.3817 4297.8321) (2414.0611 4299.3588)
      (2418.1985 4303.4962) (2419.7252 4309.1756) (2418.1985 4314.8397) (2414.0611 4318.9924) (2408.3817 4320.5038)
      (2402.7176 4318.9924) (2398.5649 4314.8397)
    ))
    ; P2805 -- see feature_dimensions_mm.csv
    ("06_ORNAMENT" 1 (
      (2397.0534 3935.0992) (2398.5649 3929.4351) (2402.7176 3925.2824) (2408.3817 3923.771) (2414.0611 3925.2824)
      (2418.1985 3929.4351) (2419.7252 3935.0992) (2418.1985 3940.7786) (2414.0611 3944.916) (2408.3817 3946.4427)
      (2402.7176 3944.916) (2398.5649 3940.7786)
    ))
    ; P2806 -- see feature_dimensions_mm.csv
    ("06_ORNAMENT" 1 (
      (2406.4885 5312.9771) (2407.2061 5307.8473) (2409.3282 5302.855) (2412.8092 5298.1069) (2417.5573 5293.7252)
      (2423.4656 5289.8168) (2430.3664 5286.4885) (2438.1221 5283.8015) (2446.5191 5281.8321) (2455.3588 5280.626)
      (2464.4275 5280.229) (2473.4962 5280.626) (2482.3359 5281.8321) (2490.7328 5283.8015) (2498.4885 5286.4885)
      (2505.3893 5289.8168) (2511.2977 5293.7252) (2516.0458 5298.1069) (2519.5267 5302.855) (2521.6489 5307.8473)
      (2522.3664 5312.9771) (2521.6489 5318.1069) (2519.5267 5323.0992) (2516.0458 5327.8473) (2511.2977 5332.229)
      (2505.3893 5336.1374) (2498.4885 5339.4656) (2490.7328 5342.1527) (2482.3359 5344.1221) (2473.4962 5345.3282)
      (2464.4275 5345.7252) (2455.3588 5345.3282) (2446.5191 5344.1221) (2438.1221 5342.1527) (2430.3664 5339.4656)
      (2423.4656 5336.1374) (2417.5573 5332.229) (2412.8092 5327.8473) (2409.3282 5323.0992) (2407.2061 5318.1069)
    ))
    ; P2807 -- see feature_dimensions_mm.csv
    ("06_ORNAMENT" 1 (
      (2406.4885 4717.5573) (2407.2061 4712.4275) (2409.3282 4707.4351) (2412.8092 4702.687) (2417.5573 4698.3053)
      (2423.4656 4694.3969) (2430.3664 4691.0687) (2438.1221 4688.3817) (2446.5191 4686.4122) (2455.3588 4685.2061)
      (2464.4275 4684.8092) (2473.4962 4685.2061) (2482.3359 4686.4122) (2490.7328 4688.3817) (2498.4885 4691.0687)
      (2505.3893 4694.3969) (2511.2977 4698.3053) (2516.0458 4702.687) (2519.5267 4707.4351) (2521.6489 4712.4275)
      (2522.3664 4717.5573) (2521.6489 4722.687) (2519.5267 4727.6794) (2516.0458 4732.4275) (2511.2977 4736.8092)
      (2505.3893 4740.7176) (2498.4885 4744.0458) (2490.7328 4746.7328) (2482.3359 4748.7023) (2473.4962 4749.9084)
      (2464.4275 4750.3053) (2455.3588 4749.9084) (2446.5191 4748.7023) (2438.1221 4746.7328) (2430.3664 4744.0458)
      (2423.4656 4740.7176) (2417.5573 4736.8092) (2412.8092 4732.4275) (2409.3282 4727.6794) (2407.2061 4722.687)
    ))
    ; P2808 -- see feature_dimensions_mm.csv
    ("06_ORNAMENT" 1 (
      (2406.4885 4122.1374) (2407.2061 4117.0076) (2409.3282 4112.0153) (2412.8092 4107.2672) (2417.5573 4102.8855)
      (2423.4656 4098.9771) (2430.3664 4095.6489) (2438.1221 4092.9618) (2446.5191 4090.9924) (2455.3588 4089.7863)
      (2464.4275 4089.3893) (2473.4962 4089.7863) (2482.3359 4090.9924) (2490.7328 4092.9618) (2498.4885 4095.6489)
      (2505.3893 4098.9771) (2511.2977 4102.8855) (2516.0458 4107.2672) (2519.5267 4112.0153) (2521.6489 4117.0076)
      (2522.3664 4122.1374) (2521.6489 4127.2672) (2519.5267 4132.2595) (2516.0458 4137.0076) (2511.2977 4141.3893)
      (2505.3893 4145.2977) (2498.4885 4148.626) (2490.7328 4151.313) (2482.3359 4153.2824) (2473.4962 4154.4885)
      (2464.4275 4154.8855) (2455.3588 4154.4885) (2446.5191 4153.2824) (2438.1221 4151.313) (2430.3664 4148.626)
      (2423.4656 4145.2977) (2417.5573 4141.3893) (2412.8092 4137.0076) (2409.3282 4132.2595) (2407.2061 4127.2672)
    ))
    ; P2809 -- see feature_dimensions_mm.csv
    ("06_ORNAMENT" 1 (
      (2418.3206 5022.9008) (2418.7328 5020.3206) (2419.9237 5017.8931) (2421.8168 5015.6947) (2424.2748 5013.8626)
      (2427.1145 5012.4122) (2430.1374 5011.3588) (2433.1756 5010.6412) (2436.0153 5010.1985) (2438.5344 5009.8779)
      (2440.626 5009.5573) (2442.2595 5009.084) (2443.4198 5008.3053) (2444.1985 5007.145) (2444.6718 5005.5115)
      (2444.9924 5003.4198) (2445.313 5000.9008) (2445.7557 4998.0611) (2446.4733 4995.0229) (2447.5267 4992.0)
      (2448.9771 4989.1603) (2450.8092 4986.7023) (2453.0076 4984.8092) (2455.4351 4983.6183) (2458.0153 4983.2061)
      (2460.5954 4983.6183) (2463.0229 4984.8092) (2465.2214 4986.7023) (2467.0534 4989.1603) (2468.5038 4992.0)
      (2469.5573 4995.0229) (2470.2748 4998.0611) (2470.7176 5000.9008) (2471.0382 5003.4198) (2471.3588 5005.5115)
      (2471.8321 5007.145) (2472.6107 5008.3053) (2473.771 5009.084) (2475.4046 5009.5573) (2477.4962 5009.8779)
      (2480.0153 5010.1985) (2482.855 5010.6412) (2485.8931 5011.3588) (2488.916 5012.4122) (2491.7557 5013.8626)
      (2494.2137 5015.6947) (2496.1069 5017.8931) (2497.2977 5020.3206) (2497.7099 5022.9008) (2497.2977 5025.4809)
      (2496.1069 5027.9084) (2494.2137 5030.1069) (2491.7557 5031.9389) (2488.916 5033.3893) (2485.8931 5034.4427)
      (2482.855 5035.1603) (2480.0153 5035.6031) (2477.4962 5035.9237) (2475.4046 5036.2443) (2473.771 5036.7176)
      (2472.6107 5037.4962) (2471.8321 5038.6565) (2471.3588 5040.2901) (2471.0382 5042.3817) (2470.7176 5044.9008)
      (2470.2748 5047.7405) (2469.5573 5050.7786) (2468.5038 5053.8015) (2467.0534 5056.6412) (2465.2214 5059.0992)
      (2463.0229 5060.9924) (2460.5954 5062.1832) (2458.0153 5062.5954) (2455.4351 5062.1832) (2453.0076 5060.9924)
      (2450.8092 5059.0992) (2448.9771 5056.6412) (2447.5267 5053.8015) (2446.4733 5050.7786) (2445.7557 5047.7405)
      (2445.313 5044.9008) (2444.9924 5042.3817) (2444.6718 5040.2901) (2444.1985 5038.6565) (2443.4198 5037.4962)
      (2442.2595 5036.7176) (2440.626 5036.2443) (2438.5344 5035.9237) (2436.0153 5035.6031) (2433.1756 5035.1603)
      (2430.1374 5034.4427) (2427.1145 5033.3893) (2424.2748 5031.9389) (2421.8168 5030.1069) (2419.9237 5027.9084)
      (2418.7328 5025.4809)
    ))
    ; P2810 -- see feature_dimensions_mm.csv
    ("06_ORNAMENT" 1 (
      (2455.771 5194.3664) (2456.6718 5188.5496) (2458.7023 5183.5115) (2461.8321 5179.3893) (2465.9542 5176.2595)
      (2470.9924 5174.229) (2476.8092 5173.3282) (2483.2672 5173.6031) (2490.1985 5175.0076) (2497.4504 5177.542)
      (2504.8244 5181.1145) (2512.1527 5185.6641) (2519.2519 5191.0687) (2525.9542 5197.1908) (2532.0763 5203.8931)
      (2537.4809 5210.9924) (2542.0305 5218.3206) (2545.6031 5225.6947) (2548.1374 5232.9466) (2549.5573 5239.8779)
      (2549.8168 5246.3359) (2548.916 5252.1527) (2546.8855 5257.1908) (2543.7557 5261.313) (2539.6336 5264.4427)
      (2534.5954 5266.4733) (2528.7786 5267.374) (2522.3206 5267.1145) (2515.3893 5265.6947) (2508.1374 5263.1603)
      (2500.7634 5259.5878) (2493.4351 5255.0382) (2486.3359 5249.6336) (2479.6336 5243.5115) (2473.5115 5236.8092)
      (2468.1069 5229.7099) (2463.5573 5222.3817) (2459.9847 5215.0076) (2457.4504 5207.7557) (2456.0458 5200.8244)
    ))
    ; P2811 -- see feature_dimensions_mm.csv
    ("06_ORNAMENT" 1 (
      (2455.771 4836.1679) (2456.0458 4829.7099) (2457.4504 4822.7786) (2459.9847 4815.5267) (2463.5573 4808.1527)
      (2468.1069 4800.8244) (2473.5115 4793.7252) (2479.6336 4787.0229) (2486.3359 4780.9008) (2493.4351 4775.4962)
      (2500.7634 4770.9466) (2508.1374 4767.374) (2515.3893 4764.8397) (2522.3206 4763.4198) (2528.7786 4763.1603)
      (2534.5954 4764.0611) (2539.6336 4766.0916) (2543.7557 4769.2214) (2546.8855 4773.3435) (2548.916 4778.3817)
      (2549.8168 4784.1985) (2549.5573 4790.6565) (2548.1374 4797.5878) (2545.6031 4804.8397) (2542.0305 4812.2137)
      (2537.4809 4819.542) (2532.0763 4826.6412) (2525.9542 4833.3435) (2519.2519 4839.4656) (2512.1527 4844.8702)
      (2504.8244 4849.4198) (2497.4504 4852.9924) (2490.1985 4855.5267) (2483.2672 4856.9313) (2476.8092 4857.2061)
      (2470.9924 4856.3053) (2465.9542 4854.2748) (2461.8321 4851.145) (2458.7023 4847.0229) (2456.6718 4841.9847)
    ))
    ; P2812 -- see feature_dimensions_mm.csv
    ("06_ORNAMENT" 1 (
      (2455.771 4598.9466) (2456.6718 4593.1298) (2458.7023 4588.0916) (2461.8321 4583.9695) (2465.9542 4580.8397)
      (2470.9924 4578.8092) (2476.8092 4577.9084) (2483.2672 4578.1832) (2490.1985 4579.5878) (2497.4504 4582.1221)
      (2504.8244 4585.6947) (2512.1527 4590.2443) (2519.2519 4595.6489) (2525.9542 4601.771) (2532.0763 4608.4733)
      (2537.4809 4615.5725) (2542.0305 4622.9008) (2545.6031 4630.2748) (2548.1374 4637.5267) (2549.5573 4644.458)
      (2549.8168 4650.916) (2548.916 4656.7328) (2546.8855 4661.771) (2543.7557 4665.8931) (2539.6336 4669.0229)
      (2534.5954 4671.0534) (2528.7786 4671.9542) (2522.3206 4671.6947) (2515.3893 4670.2748) (2508.1374 4667.7405)
      (2500.7634 4664.1679) (2493.4351 4659.6183) (2486.3359 4654.2137) (2479.6336 4648.0916) (2473.5115 4641.3893)
      (2468.1069 4634.2901) (2463.5573 4626.9618) (2459.9847 4619.5878) (2457.4504 4612.3359) (2456.0458 4605.4046)
    ))
    ; P2813 -- see feature_dimensions_mm.csv
    ("06_ORNAMENT" 1 (
      (2455.771 4240.7481) (2456.0458 4234.2901) (2457.4504 4227.3588) (2459.9847 4220.1069) (2463.5573 4212.7328)
      (2468.1069 4205.4046) (2473.5115 4198.3053) (2479.6336 4191.6031) (2486.3359 4185.4809) (2493.4351 4180.0763)
      (2500.7634 4175.5267) (2508.1374 4171.9542) (2515.3893 4169.4198) (2522.3206 4168.0) (2528.7786 4167.7405)
      (2534.5954 4168.6412) (2539.6336 4170.6718) (2543.7557 4173.8015) (2546.8855 4177.9237) (2548.916 4182.9618)
      (2549.8168 4188.7786) (2549.5573 4195.2366) (2548.1374 4202.1679) (2545.6031 4209.4198) (2542.0305 4216.7939)
      (2537.4809 4224.1221) (2532.0763 4231.2214) (2525.9542 4237.9237) (2519.2519 4244.0458) (2512.1527 4249.4504)
      (2504.8244 4254.0) (2497.4504 4257.5725) (2490.1985 4260.1069) (2483.2672 4261.5115) (2476.8092 4261.7863)
      (2470.9924 4260.8855) (2465.9542 4258.855) (2461.8321 4255.7252) (2458.7023 4251.6031) (2456.6718 4246.5649)
    ))
    ; P2814 -- see feature_dimensions_mm.csv
    ("06_ORNAMENT" 1 (
      (2455.771 4003.5267) (2456.6718 3997.7099) (2458.7023 3992.6718) (2461.8321 3988.5496) (2465.9542 3985.4198)
      (2470.9924 3983.3893) (2476.8092 3982.4885) (2483.2672 3982.7634) (2490.1985 3984.1679) (2497.4504 3986.7023)
      (2504.8244 3990.2748) (2512.1527 3994.8244) (2519.2519 4000.229) (2525.9542 4006.3511) (2532.0763 4013.0534)
      (2537.4809 4020.1527) (2542.0305 4027.4809) (2545.6031 4034.855) (2548.1374 4042.1069) (2549.5573 4049.0382)
      (2549.8168 4055.4962) (2548.916 4061.313) (2546.8855 4066.3511) (2543.7557 4070.4733) (2539.6336 4073.6031)
      (2534.5954 4075.6336) (2528.7786 4076.5344) (2522.3206 4076.2748) (2515.3893 4074.855) (2508.1374 4072.3206)
      (2500.7634 4068.7481) (2493.4351 4064.1985) (2486.3359 4058.7939) (2479.6336 4052.6718) (2473.5115 4045.9695)
      (2468.1069 4038.8702) (2463.5573 4031.542) (2459.9847 4024.1679) (2457.4504 4016.916) (2456.0458 4009.9847)
    ))
    ; P2815 -- see feature_dimensions_mm.csv
    ("06_ORNAMENT" 1 (
      (2482.8702 5068.6107) (2484.3817 5062.9466) (2488.5344 5058.7939) (2494.1985 5057.2672) (2499.8626 5058.7939)
      (2504.0153 5062.9466) (2505.542 5068.6107) (2504.0153 5074.2748) (2499.8626 5078.4275) (2494.1985 5079.9389)
      (2488.5344 5078.4275) (2484.3817 5074.2748)
    ))
    ; P2816 -- see feature_dimensions_mm.csv
    ("06_ORNAMENT" 1 (
      (2482.8702 4961.9237) (2484.3817 4956.2595) (2488.5344 4952.1069) (2494.1985 4950.5954) (2499.8626 4952.1069)
      (2504.0153 4956.2595) (2505.542 4961.9237) (2504.0153 4967.5878) (2499.8626 4971.7405) (2494.1985 4973.2672)
      (2488.5344 4971.7405) (2484.3817 4967.5878)
    ))
    ; P2817 -- see feature_dimensions_mm.csv
    ("06_ORNAMENT" 1 (
      (2482.8702 4366.5038) (2484.3817 4360.8397) (2488.5344 4356.687) (2494.1985 4355.1756) (2499.8626 4356.687)
      (2504.0153 4360.8397) (2505.542 4366.5038) (2504.0153 4372.1679) (2499.8626 4376.3206) (2494.1985 4377.8473)
      (2488.5344 4376.3206) (2484.3817 4372.1679)
    ))
    ; P2818 -- see feature_dimensions_mm.csv
    ("06_ORNAMENT" 1 (
      (2482.8702 3877.771) (2484.3817 3872.1069) (2488.5344 3867.9542) (2494.1985 3866.4275) (2499.8626 3867.9542)
      (2504.0153 3872.1069) (2505.542 3877.771) (2504.0153 3883.4351) (2499.8626 3887.5878) (2494.1985 3889.0992)
      (2488.5344 3887.5878) (2484.3817 3883.4351)
    ))
    ; P2819 -- see feature_dimensions_mm.csv
    ("06_ORNAMENT" 1 (
      (2489.2519 5117.4809) (2490.4885 5109.6947) (2494.0611 5102.6718) (2499.6336 5097.0992) (2506.6565 5093.5267)
      (2514.4427 5092.2901) (2522.229 5093.5267) (2529.2519 5097.0992) (2534.8244 5102.6718) (2538.3969 5109.6947)
      (2539.6336 5117.4809) (2538.3969 5125.2672) (2534.8244 5132.2901) (2529.2519 5137.8626) (2522.229 5141.4351)
      (2514.4427 5142.6718) (2506.6565 5141.4351) (2499.6336 5137.8626) (2494.0611 5132.2901) (2490.4885 5125.2672)
    ))
    ; P2820 -- see feature_dimensions_mm.csv
    ("06_ORNAMENT" 1 (
      (2489.2519 4913.0534) (2490.4885 4905.2672) (2494.0611 4898.2443) (2499.6336 4892.6718) (2506.6565 4889.0992)
      (2514.4427 4887.8626) (2522.229 4889.0992) (2529.2519 4892.6718) (2534.8244 4898.2443) (2538.3969 4905.2672)
      (2539.6336 4913.0534) (2538.3969 4920.8397) (2534.8244 4927.8626) (2529.2519 4933.4351) (2522.229 4937.0076)
      (2514.4427 4938.2443) (2506.6565 4937.0076) (2499.6336 4933.4351) (2494.0611 4927.8626) (2490.4885 4920.8397)
    ))
    ; P2821 -- see feature_dimensions_mm.csv
    ("06_ORNAMENT" 1 (
      (2489.2519 4522.0611) (2490.4885 4514.2748) (2494.0611 4507.2519) (2499.6336 4501.6794) (2506.6565 4498.1069)
      (2514.4427 4496.8702) (2522.229 4498.1069) (2529.2519 4501.6794) (2534.8244 4507.2519) (2538.3969 4514.2748)
      (2539.6336 4522.0611) (2538.3969 4529.8473) (2534.8244 4536.8702) (2529.2519 4542.4427) (2522.229 4546.0153)
      (2514.4427 4547.2519) (2506.6565 4546.0153) (2499.6336 4542.4427) (2494.0611 4536.8702) (2490.4885 4529.8473)
    ))
    ; P2822 -- see feature_dimensions_mm.csv
    ("06_ORNAMENT" 1 (
      (2489.2519 4317.6336) (2490.4885 4309.8473) (2494.0611 4302.8244) (2499.6336 4297.2519) (2506.6565 4293.6794)
      (2514.4427 4292.4427) (2522.229 4293.6794) (2529.2519 4297.2519) (2534.8244 4302.8244) (2538.3969 4309.8473)
      (2539.6336 4317.6336) (2538.3969 4325.4198) (2534.8244 4332.4427) (2529.2519 4338.0153) (2522.229 4341.5878)
      (2514.4427 4342.8244) (2506.6565 4341.5878) (2499.6336 4338.0153) (2494.0611 4332.4427) (2490.4885 4325.4198)
    ))
    ; P2823 -- see feature_dimensions_mm.csv
    ("06_ORNAMENT" 1 (
      (2489.2519 3926.6412) (2490.4885 3918.855) (2494.0611 3911.8321) (2499.6336 3906.2595) (2506.6565 3902.687)
      (2514.4427 3901.4504) (2522.229 3902.687) (2529.2519 3906.2595) (2534.8244 3911.8321) (2538.3969 3918.855)
      (2539.6336 3926.6412) (2538.3969 3934.4275) (2534.8244 3941.4504) (2529.2519 3947.0229) (2522.229 3950.5954)
      (2514.4427 3951.8321) (2506.6565 3950.5954) (2499.6336 3947.0229) (2494.0611 3941.4504) (2490.4885 3934.4275)
    ))
    ; P2824 -- see feature_dimensions_mm.csv
    ("06_ORNAMENT" 1 (
      (2534.9618 5312.9771) (2536.1221 5301.1756) (2539.5573 5289.8473) (2545.145 5279.3893) (2552.6718 5270.229)
      (2561.8321 5262.7023) (2572.2901 5257.1145) (2583.6183 5253.6794) (2595.4198 5252.5191) (2607.2214 5253.6794)
      (2618.5496 5257.1145) (2629.0076 5262.7023) (2638.1679 5270.229) (2645.6947 5279.3893) (2651.2824 5289.8473)
      (2654.7176 5301.1756) (2655.8779 5312.9771) (2654.7176 5324.7786) (2651.2824 5336.1069) (2645.6947 5346.5649)
      (2638.1679 5355.7252) (2629.0076 5363.2519) (2618.5496 5368.8397) (2607.2214 5372.2748) (2595.4198 5373.4351)
      (2583.6183 5372.2748) (2572.2901 5368.8397) (2561.8321 5363.2519) (2552.6718 5355.7252) (2545.145 5346.5649)
      (2539.5573 5336.1069) (2536.1221 5324.7786)
    ))
    ; P2825 -- see feature_dimensions_mm.csv
    ("06_ORNAMENT" 1 (
      (2534.9618 4717.5573) (2536.1221 4705.7557) (2539.5573 4694.4275) (2545.145 4683.9695) (2552.6718 4674.8092)
      (2561.8321 4667.2824) (2572.2901 4661.6947) (2583.6183 4658.2595) (2595.4198 4657.0992) (2607.2214 4658.2595)
      (2618.5496 4661.6947) (2629.0076 4667.2824) (2638.1679 4674.8092) (2645.6947 4683.9695) (2651.2824 4694.4275)
      (2654.7176 4705.7557) (2655.8779 4717.5573) (2654.7176 4729.3588) (2651.2824 4740.687) (2645.6947 4751.145)
      (2638.1679 4760.3053) (2629.0076 4767.8321) (2618.5496 4773.4198) (2607.2214 4776.855) (2595.4198 4778.0153)
      (2583.6183 4776.855) (2572.2901 4773.4198) (2561.8321 4767.8321) (2552.6718 4760.3053) (2545.145 4751.145)
      (2539.5573 4740.687) (2536.1221 4729.3588)
    ))
    ; P2826 -- see feature_dimensions_mm.csv
    ("06_ORNAMENT" 1 (
      (2534.9618 4122.1374) (2536.1221 4110.3359) (2539.5573 4099.0076) (2545.145 4088.5496) (2552.6718 4079.3893)
      (2561.8321 4071.8626) (2572.2901 4066.2748) (2583.6183 4062.8397) (2595.4198 4061.6794) (2607.2214 4062.8397)
      (2618.5496 4066.2748) (2629.0076 4071.8626) (2638.1679 4079.3893) (2645.6947 4088.5496) (2651.2824 4099.0076)
      (2654.7176 4110.3359) (2655.8779 4122.1374) (2654.7176 4133.9389) (2651.2824 4145.2672) (2645.6947 4155.7252)
      (2638.1679 4164.8855) (2629.0076 4172.4122) (2618.5496 4178.0) (2607.2214 4181.4351) (2595.4198 4182.5954)
      (2583.6183 4181.4351) (2572.2901 4178.0) (2561.8321 4172.4122) (2552.6718 4164.8855) (2545.145 4155.7252)
      (2539.5573 4145.2672) (2536.1221 4133.9389)
    ))
    ; P2827 -- see feature_dimensions_mm.csv
    ("06_ORNAMENT" 1 (
      (2545.2366 2064.3206) (2547.1145 2052.5344) (2552.5344 2041.8931) (2560.9771 2033.4504) (2571.6183 2028.0305)
      (2583.4046 2026.1527) (2595.2061 2028.0305) (2605.8473 2033.4504) (2614.2901 2041.8931) (2619.7099 2052.5344)
      (2621.5725 2064.3206) (2619.7099 2076.1221) (2614.2901 2086.7634) (2605.8473 2095.2061) (2595.2061 2100.626)
      (2583.4046 2102.4885) (2571.6183 2100.626) (2560.9771 2095.2061) (2552.5344 2086.7634) (2547.1145 2076.1221)
    ))
    ; P2828 -- see feature_dimensions_mm.csv
    ("06_ORNAMENT" 1 (
      (2546.4122 1392.3053) (2547.6794 1395.9847) (2549.4504 1400.1985) (2552.5344 1394.1527) (2559.9237 1386.7634)
      (2557.7252 1387.1603) (2552.3817 1387.8473) (2548.5649 1388.5802) (2546.5802 1389.9237)
    ))
    ; P2829 -- see feature_dimensions_mm.csv
    ("06_ORNAMENT" 1 (
      (2559.3893 3007.6336) (2560.1069 3006.3206) (2562.0305 3005.2519) (2564.6718 3004.5496) (2567.313 3004.1985)
      (2569.2977 3003.9542) (2570.1832 3003.4962) (2569.8779 3002.5649) (2568.6412 3000.9924) (2567.0382 2998.8702)
      (2565.6641 2996.5038) (2565.0382 2994.3817) (2565.4656 2992.9466) (2566.9008 2992.5191) (2569.0229 2993.145)
      (2571.3893 2994.5191) (2573.5115 2996.1221) (2575.084 2997.3588) (2576.0153 2997.6641) (2576.4733 2996.7786)
      (2576.7176 2994.7939) (2577.0687 2992.1527) (2577.771 2989.5115) (2578.8397 2987.5878) (2580.1527 2986.8702)
      (2581.4656 2987.5878) (2582.5344 2989.5115) (2583.2366 2992.1527) (2583.5878 2994.7939) (2583.8321 2996.7786)
      (2584.2901 2997.6641) (2585.2214 2997.3588) (2586.7939 2996.1221) (2588.916 2994.5191) (2591.2824 2993.145)
      (2593.4046 2992.5191) (2594.8397 2992.9466) (2595.2672 2994.3817) (2594.6412 2996.5038) (2593.2672 2998.8702)
      (2591.6641 3000.9924) (2590.4275 3002.5649) (2590.1221 3003.4962) (2591.0076 3003.9542) (2592.9924 3004.1985)
      (2595.6336 3004.5496) (2598.2748 3005.2519) (2600.1985 3006.3206) (2600.916 3007.6336) (2600.1985 3008.9466)
      (2598.2748 3010.0153) (2595.6336 3010.7176) (2592.9924 3011.0687) (2591.0076 3011.313) (2590.1221 3011.771)
      (2590.4275 3012.7023) (2591.6641 3014.2748) (2593.2672 3016.3969) (2594.6412 3018.7634) (2595.2672 3020.8855)
      (2594.8397 3022.3206) (2593.4046 3022.7481) (2591.2824 3022.1221) (2588.916 3020.7481) (2586.7939 3019.145)
      (2585.2214 3017.9084) (2584.2901 3017.6031) (2583.8321 3018.4885) (2583.5878 3020.4733) (2583.2366 3023.1145)
      (2582.5344 3025.7557) (2581.4656 3027.6794) (2580.1527 3028.3969) (2578.8397 3027.6794) (2577.771 3025.7557)
      (2577.0687 3023.1145) (2576.7176 3020.4733) (2576.4733 3018.4885) (2576.0153 3017.6031) (2575.084 3017.9084)
      (2573.5115 3019.145) (2571.3893 3020.7481) (2569.0229 3022.1221) (2566.9008 3022.7481) (2565.4656 3022.3206)
      (2565.0382 3020.8855) (2565.6641 3018.7634) (2567.0382 3016.3969) (2568.6412 3014.2748) (2569.8779 3012.7023)
      (2570.1832 3011.771) (2569.2977 3011.313) (2567.313 3011.0687) (2564.6718 3010.7176) (2562.0305 3010.0153)
      (2560.1069 3008.9466)
    ))
    ; P2830 -- see feature_dimensions_mm.csv
    ("06_ORNAMENT" 1 (
      (2559.3893 2900.7634) (2560.1069 2899.4504) (2562.0305 2898.3817) (2564.6718 2897.6794) (2567.313 2897.3282)
      (2569.2977 2897.084) (2570.1832 2896.626) (2569.8779 2895.6947) (2568.6412 2894.1221) (2567.0382 2892.0)
      (2565.6641 2889.6336) (2565.0382 2887.5115) (2565.4656 2886.0763) (2566.9008 2885.6489) (2569.0229 2886.2748)
      (2571.3893 2887.6489) (2573.5115 2889.2519) (2575.084 2890.4885) (2576.0153 2890.7939) (2576.4733 2889.9084)
      (2576.7176 2887.9237) (2577.0687 2885.2824) (2577.771 2882.6412) (2578.8397 2880.7176) (2580.1527 2880.0)
      (2581.4656 2880.7176) (2582.5344 2882.6412) (2583.2366 2885.2824) (2583.5878 2887.9237) (2583.8321 2889.9084)
      (2584.2901 2890.7939) (2585.2214 2890.4885) (2586.7939 2889.2519) (2588.916 2887.6489) (2591.2824 2886.2748)
      (2593.4046 2885.6489) (2594.8397 2886.0763) (2595.2672 2887.5115) (2594.6412 2889.6336) (2593.2672 2892.0)
      (2591.6641 2894.1221) (2590.4275 2895.6947) (2590.1221 2896.626) (2591.0076 2897.084) (2592.9924 2897.3282)
      (2595.6336 2897.6794) (2598.2748 2898.3817) (2600.1985 2899.4504) (2600.916 2900.7634) (2600.1985 2902.0763)
      (2598.2748 2903.145) (2595.6336 2903.8473) (2592.9924 2904.1985) (2591.0076 2904.4427) (2590.1221 2904.9008)
      (2590.4275 2905.8321) (2591.6641 2907.4046) (2593.2672 2909.5267) (2594.6412 2911.8931) (2595.2672 2914.0153)
      (2594.8397 2915.4504) (2593.4046 2915.8779) (2591.2824 2915.2519) (2588.916 2913.8779) (2586.7939 2912.2748)
      (2585.2214 2911.0382) (2584.2901 2910.7328) (2583.8321 2911.6183) (2583.5878 2913.6031) (2583.2366 2916.2443)
      (2582.5344 2918.8855) (2581.4656 2920.8092) (2580.1527 2921.5267) (2578.8397 2920.8092) (2577.771 2918.8855)
      (2577.0687 2916.2443) (2576.7176 2913.6031) (2576.4733 2911.6183) (2576.0153 2910.7328) (2575.084 2911.0382)
      (2573.5115 2912.2748) (2571.3893 2913.8779) (2569.0229 2915.2519) (2566.9008 2915.8779) (2565.4656 2915.4504)
      (2565.0382 2914.0153) (2565.6641 2911.8931) (2567.0382 2909.5267) (2568.6412 2907.4046) (2569.8779 2905.8321)
      (2570.1832 2904.9008) (2569.2977 2904.4427) (2567.313 2904.1985) (2564.6718 2903.8473) (2562.0305 2903.145)
      (2560.1069 2902.0763)
    ))
    ; P2831 -- see feature_dimensions_mm.csv
    ("06_ORNAMENT" 1 (
      (2560.1527 5312.9771) (2561.3588 5303.8473) (2564.8702 5295.3435) (2570.4885 5288.0458) (2577.7863 5282.4275)
      (2586.2901 5278.916) (2595.4198 5277.7099) (2604.5496 5278.916) (2613.0534 5282.4275) (2620.3511 5288.0458)
      (2625.9695 5295.3435) (2629.4809 5303.8473) (2630.687 5312.9771) (2629.4809 5322.1069) (2625.9695 5330.6107)
      (2620.3511 5337.9084) (2613.0534 5343.5267) (2604.5496 5347.0382) (2595.4198 5348.2443) (2586.2901 5347.0382)
      (2577.7863 5343.5267) (2570.4885 5337.9084) (2564.8702 5330.6107) (2561.3588 5322.1069)
    ))
    ; P2832 -- see feature_dimensions_mm.csv
    ("06_ORNAMENT" 1 (
      (2560.1527 4717.5573) (2561.3588 4708.4275) (2564.8702 4699.9237) (2570.4885 4692.626) (2577.7863 4687.0076)
      (2586.2901 4683.4962) (2595.4198 4682.2901) (2604.5496 4683.4962) (2613.0534 4687.0076) (2620.3511 4692.626)
      (2625.9695 4699.9237) (2629.4809 4708.4275) (2630.687 4717.5573) (2629.4809 4726.687) (2625.9695 4735.1908)
      (2620.3511 4742.4885) (2613.0534 4748.1069) (2604.5496 4751.6183) (2595.4198 4752.8244) (2586.2901 4751.6183)
      (2577.7863 4748.1069) (2570.4885 4742.4885) (2564.8702 4735.1908) (2561.3588 4726.687)
    ))
    ; P2833 -- see feature_dimensions_mm.csv
    ("06_ORNAMENT" 1 (
      (2560.1527 4122.1374) (2561.3588 4113.0076) (2564.8702 4104.5038) (2570.4885 4097.2061) (2577.7863 4091.5878)
      (2586.2901 4088.0763) (2595.4198 4086.8702) (2604.5496 4088.0763) (2613.0534 4091.5878) (2620.3511 4097.2061)
      (2625.9695 4104.5038) (2629.4809 4113.0076) (2630.687 4122.1374) (2629.4809 4131.2672) (2625.9695 4139.771)
      (2620.3511 4147.0687) (2613.0534 4152.687) (2604.5496 4156.1985) (2595.4198 4157.4046) (2586.2901 4156.1985)
      (2577.7863 4152.687) (2570.4885 4147.0687) (2564.8702 4139.771) (2561.3588 4131.2672)
    ))
    ; P2834 -- see feature_dimensions_mm.csv
    ("06_ORNAMENT" 1 (
      (2562.6718 5181.9847) (2563.0687 5172.916) (2564.2748 5164.0763) (2566.2443 5155.6794) (2568.9313 5147.9237)
      (2572.2595 5141.0229) (2576.1679 5135.1145) (2580.5496 5130.3664) (2585.2977 5126.8855) (2590.2901 5124.7634)
      (2595.4198 5124.0458) (2600.5496 5124.7634) (2605.542 5126.8855) (2610.2901 5130.3664) (2614.6718 5135.1145)
      (2618.5802 5141.0229) (2621.9084 5147.9237) (2624.5954 5155.6794) (2626.5649 5164.0763) (2627.771 5172.916)
      (2628.1679 5181.9847) (2627.771 5191.0534) (2626.5649 5199.8931) (2624.5954 5208.2901) (2621.9084 5216.0458)
      (2618.5802 5222.9466) (2614.6718 5228.855) (2610.2901 5233.6031) (2605.542 5237.084) (2600.5496 5239.2061)
      (2595.4198 5239.9237) (2590.2901 5239.2061) (2585.2977 5237.084) (2580.5496 5233.6031) (2576.1679 5228.855)
      (2572.2595 5222.9466) (2568.9313 5216.0458) (2566.2443 5208.2901) (2564.2748 5199.8931) (2563.0687 5191.0534)
    ))
    ; P2835 -- see feature_dimensions_mm.csv
    ("06_ORNAMENT" 1 (
      (2562.6718 4848.5496) (2563.0687 4839.4809) (2564.2748 4830.6412) (2566.2443 4822.2443) (2568.9313 4814.4885)
      (2572.2595 4807.5878) (2576.1679 4801.6794) (2580.5496 4796.9313) (2585.2977 4793.4504) (2590.2901 4791.3282)
      (2595.4198 4790.6107) (2600.5496 4791.3282) (2605.542 4793.4504) (2610.2901 4796.9313) (2614.6718 4801.6794)
      (2618.5802 4807.5878) (2621.9084 4814.4885) (2624.5954 4822.2443) (2626.5649 4830.6412) (2627.771 4839.4809)
      (2628.1679 4848.5496) (2627.771 4857.6183) (2626.5649 4866.458) (2624.5954 4874.855) (2621.9084 4882.6107)
      (2618.5802 4889.5115) (2614.6718 4895.4198) (2610.2901 4900.1679) (2605.542 4903.6489) (2600.5496 4905.771)
      (2595.4198 4906.4885) (2590.2901 4905.771) (2585.2977 4903.6489) (2580.5496 4900.1679) (2576.1679 4895.4198)
      (2572.2595 4889.5115) (2568.9313 4882.6107) (2566.2443 4874.855) (2564.2748 4866.458) (2563.0687 4857.6183)
    ))
    ; P2836 -- see feature_dimensions_mm.csv
    ("06_ORNAMENT" 1 (
      (2562.6718 4253.1298) (2563.0687 4244.0611) (2564.2748 4235.2214) (2566.2443 4226.8244) (2568.9313 4219.0687)
      (2572.2595 4212.1679) (2576.1679 4206.2595) (2580.5496 4201.5115) (2585.2977 4198.0305) (2590.2901 4195.9084)
      (2595.4198 4195.1908) (2600.5496 4195.9084) (2605.542 4198.0305) (2610.2901 4201.5115) (2614.6718 4206.2595)
      (2618.5802 4212.1679) (2621.9084 4219.0687) (2624.5954 4226.8244) (2626.5649 4235.2214) (2627.771 4244.0611)
      (2628.1679 4253.1298) (2627.771 4262.1985) (2626.5649 4271.0382) (2624.5954 4279.4351) (2621.9084 4287.1908)
      (2618.5802 4294.0916) (2614.6718 4300.0) (2610.2901 4304.7481) (2605.542 4308.229) (2600.5496 4310.3511)
      (2595.4198 4311.0687) (2590.2901 4310.3511) (2585.2977 4308.229) (2580.5496 4304.7481) (2576.1679 4300.0)
      (2572.2595 4294.0916) (2568.9313 4287.1908) (2566.2443 4279.4351) (2564.2748 4271.0382) (2563.0687 4262.1985)
    ))
    ; P2837 -- see feature_dimensions_mm.csv
    ("06_ORNAMENT" 1 (
      (2562.6718 3991.145) (2563.0687 3982.0763) (2564.2748 3973.2366) (2566.2443 3964.8397) (2568.9313 3957.084)
      (2572.2595 3950.1832) (2576.1679 3944.2748) (2580.5496 3939.5267) (2585.2977 3936.0458) (2590.2901 3933.9237)
      (2595.4198 3933.2061) (2600.5496 3933.9237) (2605.542 3936.0458) (2610.2901 3939.5267) (2614.6718 3944.2748)
      (2618.5802 3950.1832) (2621.9084 3957.084) (2624.5954 3964.8397) (2626.5649 3973.2366) (2627.771 3982.0763)
      (2628.1679 3991.145) (2627.771 4000.2137) (2626.5649 4009.0534) (2624.5954 4017.4504) (2621.9084 4025.2061)
      (2618.5802 4032.1069) (2614.6718 4038.0153) (2610.2901 4042.7634) (2605.542 4046.2443) (2600.5496 4048.3664)
      (2595.4198 4049.084) (2590.2901 4048.3664) (2585.2977 4046.2443) (2580.5496 4042.7634) (2576.1679 4038.0153)
      (2572.2595 4032.1069) (2568.9313 4025.2061) (2566.2443 4017.4504) (2564.2748 4009.0534) (2563.0687 4000.2137)
    ))
    ; P2838 -- see feature_dimensions_mm.csv
    ("06_ORNAMENT" 1 (
      (2574.0458 3007.6336) (2574.5038 3005.2977) (2575.8321 3003.313) (2577.8168 3001.9847) (2580.1527 3001.5267)
      (2582.4885 3001.9847) (2584.4733 3003.313) (2585.8015 3005.2977) (2586.2595 3007.6336) (2585.8015 3009.9695)
      (2584.4733 3011.9542) (2582.4885 3013.2824) (2580.1527 3013.7405) (2577.8168 3013.2824) (2575.8321 3011.9542)
      (2574.5038 3009.9695)
    ))
    ; P2839 -- see feature_dimensions_mm.csv
    ("06_ORNAMENT" 1 (
      (2574.0458 2900.7634) (2574.5038 2898.4275) (2575.8321 2896.4427) (2577.8168 2895.1145) (2580.1527 2894.6565)
      (2582.4885 2895.1145) (2584.4733 2896.4427) (2585.8015 2898.4275) (2586.2595 2900.7634) (2585.8015 2903.0992)
      (2584.4733 2905.084) (2582.4885 2906.4122) (2580.1527 2906.8702) (2577.8168 2906.4122) (2575.8321 2905.084)
      (2574.5038 2903.0992)
    ))
    ; P2840 -- see feature_dimensions_mm.csv
    ("06_ORNAMENT" 1 (
      (2584.0916 5048.4733) (2585.6031 5042.8092) (2589.7557 5038.6565) (2595.4198 5037.1298) (2601.084 5038.6565)
      (2605.2366 5042.8092) (2606.7634 5048.4733) (2605.2366 5054.1374) (2601.084 5058.2901) (2595.4198 5059.8015)
      (2589.7557 5058.2901) (2585.6031 5054.1374)
    ))
    ; P2841 -- see feature_dimensions_mm.csv
    ("06_ORNAMENT" 1 (
      (2584.0916 3857.6336) (2585.6031 3851.9695) (2589.7557 3847.8168) (2595.4198 3846.2901) (2601.084 3847.8168)
      (2605.2366 3851.9695) (2606.7634 3857.6336) (2605.2366 3863.2977) (2601.084 3867.4504) (2595.4198 3868.9618)
      (2589.7557 3867.4504) (2585.6031 3863.2977)
    ))
    ; P2842 -- see feature_dimensions_mm.csv
    ("06_ORNAMENT" 1 (
      (2641.0229 5379.6183) (2641.9237 5373.8015) (2643.9542 5368.7634) (2647.084 5364.6412) (2651.2061 5361.5115)
      (2656.2443 5359.4809) (2662.0611 5358.5802) (2668.5191 5358.8397) (2675.4504 5360.2595) (2682.7023 5362.7939)
      (2690.0763 5366.3664) (2697.4046 5370.916) (2704.5038 5376.3206) (2711.2061 5382.4427) (2717.3282 5389.145)
      (2722.7328 5396.2443) (2727.2824 5403.5725) (2730.855 5410.9466) (2733.3893 5418.1985) (2734.7939 5425.1298)
      (2735.0687 5431.5878) (2734.1679 5437.4046) (2732.1374 5442.4427) (2729.0076 5446.5649) (2724.8855 5449.6947)
      (2719.8473 5451.7252) (2714.0305 5452.626) (2707.5725 5452.3511) (2700.6412 5450.9466) (2693.3893 5448.4122)
      (2686.0153 5444.8397) (2678.687 5440.2901) (2671.5878 5434.8855) (2664.8855 5428.7634) (2658.7634 5422.0611)
      (2653.3588 5414.9618) (2648.8092 5407.6336) (2645.2366 5400.2595) (2642.7023 5393.0076) (2641.2824 5386.0763)
    ))
    ; P2843 -- see feature_dimensions_mm.csv
    ("06_ORNAMENT" 1 (
      (2641.0229 5246.3359) (2641.2824 5239.8779) (2642.7023 5232.9466) (2645.2366 5225.6947) (2648.8092 5218.3206)
      (2653.3588 5210.9924) (2658.7634 5203.8931) (2664.8855 5197.1908) (2671.5878 5191.0687) (2678.687 5185.6641)
      (2686.0153 5181.1145) (2693.3893 5177.542) (2700.6412 5175.0076) (2707.5725 5173.6031) (2714.0305 5173.3282)
      (2719.8473 5174.229) (2724.8855 5176.2595) (2729.0076 5179.3893) (2732.1374 5183.5115) (2734.1679 5188.5496)
      (2735.0687 5194.3664) (2734.7939 5200.8244) (2733.3893 5207.7557) (2730.855 5215.0076) (2727.2824 5222.3817)
      (2722.7328 5229.7099) (2717.3282 5236.8092) (2711.2061 5243.5115) (2704.5038 5249.6336) (2697.4046 5255.0382)
      (2690.0763 5259.5878) (2682.7023 5263.1603) (2675.4504 5265.6947) (2668.5191 5267.1145) (2662.0611 5267.374)
      (2656.2443 5266.4733) (2651.2061 5264.4427) (2647.084 5261.313) (2643.9542 5257.1908) (2641.9237 5252.1527)
    ))
    ; P2844 -- see feature_dimensions_mm.csv
    ("06_ORNAMENT" 1 (
      (2641.0229 4784.1985) (2641.9237 4778.3817) (2643.9542 4773.3435) (2647.084 4769.2214) (2651.2061 4766.0916)
      (2656.2443 4764.0611) (2662.0611 4763.1603) (2668.5191 4763.4198) (2675.4504 4764.8397) (2682.7023 4767.374)
      (2690.0763 4770.9466) (2697.4046 4775.4962) (2704.5038 4780.9008) (2711.2061 4787.0229) (2717.3282 4793.7252)
      (2722.7328 4800.8244) (2727.2824 4808.1527) (2730.855 4815.5267) (2733.3893 4822.7786) (2734.7939 4829.7099)
      (2735.0687 4836.1679) (2734.1679 4841.9847) (2732.1374 4847.0229) (2729.0076 4851.145) (2724.8855 4854.2748)
      (2719.8473 4856.3053) (2714.0305 4857.2061) (2707.5725 4856.9313) (2700.6412 4855.5267) (2693.3893 4852.9924)
      (2686.0153 4849.4198) (2678.687 4844.8702) (2671.5878 4839.4656) (2664.8855 4833.3435) (2658.7634 4826.6412)
      (2653.3588 4819.542) (2648.8092 4812.2137) (2645.2366 4804.8397) (2642.7023 4797.5878) (2641.2824 4790.6565)
    ))
    ; P2845 -- see feature_dimensions_mm.csv
    ("06_ORNAMENT" 1 (
      (2641.0229 4650.916) (2641.2824 4644.458) (2642.7023 4637.5267) (2645.2366 4630.2748) (2648.8092 4622.9008)
      (2653.3588 4615.5725) (2658.7634 4608.4733) (2664.8855 4601.771) (2671.5878 4595.6489) (2678.687 4590.2443)
      (2686.0153 4585.6947) (2693.3893 4582.1221) (2700.6412 4579.5878) (2707.5725 4578.1832) (2714.0305 4577.9084)
      (2719.8473 4578.8092) (2724.8855 4580.8397) (2729.0076 4583.9695) (2732.1374 4588.0916) (2734.1679 4593.1298)
      (2735.0687 4598.9466) (2734.7939 4605.4046) (2733.3893 4612.3359) (2730.855 4619.5878) (2727.2824 4626.9618)
      (2722.7328 4634.2901) (2717.3282 4641.3893) (2711.2061 4648.0916) (2704.5038 4654.2137) (2697.4046 4659.6183)
      (2690.0763 4664.1679) (2682.7023 4667.7405) (2675.4504 4670.2748) (2668.5191 4671.6947) (2662.0611 4671.9542)
      (2656.2443 4671.0534) (2651.2061 4669.0229) (2647.084 4665.8931) (2643.9542 4661.771) (2641.9237 4656.7328)
    ))
    ; P2846 -- see feature_dimensions_mm.csv
    ("06_ORNAMENT" 1 (
      (2641.0229 4188.7786) (2641.9237 4182.9618) (2643.9542 4177.9237) (2647.084 4173.8015) (2651.2061 4170.6718)
      (2656.2443 4168.6412) (2662.0611 4167.7405) (2668.5191 4168.0) (2675.4504 4169.4198) (2682.7023 4171.9542)
      (2690.0763 4175.5267) (2697.4046 4180.0763) (2704.5038 4185.4809) (2711.2061 4191.6031) (2717.3282 4198.3053)
      (2722.7328 4205.4046) (2727.2824 4212.7328) (2730.855 4220.1069) (2733.3893 4227.3588) (2734.7939 4234.2901)
      (2735.0687 4240.7481) (2734.1679 4246.5649) (2732.1374 4251.6031) (2729.0076 4255.7252) (2724.8855 4258.855)
      (2719.8473 4260.8855) (2714.0305 4261.7863) (2707.5725 4261.5115) (2700.6412 4260.1069) (2693.3893 4257.5725)
      (2686.0153 4254.0) (2678.687 4249.4504) (2671.5878 4244.0458) (2664.8855 4237.9237) (2658.7634 4231.2214)
      (2653.3588 4224.1221) (2648.8092 4216.7939) (2645.2366 4209.4198) (2642.7023 4202.1679) (2641.2824 4195.2366)
    ))
    ; P2847 -- see feature_dimensions_mm.csv
    ("06_ORNAMENT" 1 (
      (2641.0229 4055.4962) (2641.2824 4049.0382) (2642.7023 4042.1069) (2645.2366 4034.855) (2648.8092 4027.4809)
      (2653.3588 4020.1527) (2658.7634 4013.0534) (2664.8855 4006.3511) (2671.5878 4000.229) (2678.687 3994.8244)
      (2686.0153 3990.2748) (2693.3893 3986.7023) (2700.6412 3984.1679) (2707.5725 3982.7634) (2714.0305 3982.4885)
      (2719.8473 3983.3893) (2724.8855 3985.4198) (2729.0076 3988.5496) (2732.1374 3992.6718) (2734.1679 3997.7099)
      (2735.0687 4003.5267) (2734.7939 4009.9847) (2733.3893 4016.916) (2730.855 4024.1679) (2727.2824 4031.542)
      (2722.7328 4038.8702) (2717.3282 4045.9695) (2711.2061 4052.6718) (2704.5038 4058.7939) (2697.4046 4064.1985)
      (2690.0763 4068.7481) (2682.7023 4072.3206) (2675.4504 4074.855) (2668.5191 4076.2748) (2662.0611 4076.5344)
      (2656.2443 4075.6336) (2651.2061 4073.6031) (2647.084 4070.4733) (2643.9542 4066.3511) (2641.9237 4061.313)
    ))
    ; P2848 -- see feature_dimensions_mm.csv
    ("06_ORNAMENT" 1 (
      (2651.2061 5117.4809) (2652.4427 5109.6947) (2656.0153 5102.6718) (2661.5878 5097.0992) (2668.6107 5093.5267)
      (2676.3969 5092.2901) (2684.1832 5093.5267) (2691.2061 5097.0992) (2696.7786 5102.6718) (2700.3511 5109.6947)
      (2701.5878 5117.4809) (2700.3511 5125.2672) (2696.7786 5132.2901) (2691.2061 5137.8626) (2684.1832 5141.4351)
      (2676.3969 5142.6718) (2668.6107 5141.4351) (2661.5878 5137.8626) (2656.0153 5132.2901) (2652.4427 5125.2672)
    ))
    ; P2849 -- see feature_dimensions_mm.csv
    ("06_ORNAMENT" 1 (
      (2651.2061 4913.0534) (2652.4427 4905.2672) (2656.0153 4898.2443) (2661.5878 4892.6718) (2668.6107 4889.0992)
      (2676.3969 4887.8626) (2684.1832 4889.0992) (2691.2061 4892.6718) (2696.7786 4898.2443) (2700.3511 4905.2672)
      (2701.5878 4913.0534) (2700.3511 4920.8397) (2696.7786 4927.8626) (2691.2061 4933.4351) (2684.1832 4937.0076)
      (2676.3969 4938.2443) (2668.6107 4937.0076) (2661.5878 4933.4351) (2656.0153 4927.8626) (2652.4427 4920.8397)
    ))
    ; P2850 -- see feature_dimensions_mm.csv
    ("06_ORNAMENT" 1 (
      (2651.2061 4522.0611) (2652.4427 4514.2748) (2656.0153 4507.2519) (2661.5878 4501.6794) (2668.6107 4498.1069)
      (2676.3969 4496.8702) (2684.1832 4498.1069) (2691.2061 4501.6794) (2696.7786 4507.2519) (2700.3511 4514.2748)
      (2701.5878 4522.0611) (2700.3511 4529.8473) (2696.7786 4536.8702) (2691.2061 4542.4427) (2684.1832 4546.0153)
      (2676.3969 4547.2519) (2668.6107 4546.0153) (2661.5878 4542.4427) (2656.0153 4536.8702) (2652.4427 4529.8473)
    ))
    ; P2851 -- see feature_dimensions_mm.csv
    ("06_ORNAMENT" 1 (
      (2651.2061 4317.6336) (2652.4427 4309.8473) (2656.0153 4302.8244) (2661.5878 4297.2519) (2668.6107 4293.6794)
      (2676.3969 4292.4427) (2684.1832 4293.6794) (2691.2061 4297.2519) (2696.7786 4302.8244) (2700.3511 4309.8473)
      (2701.5878 4317.6336) (2700.3511 4325.4198) (2696.7786 4332.4427) (2691.2061 4338.0153) (2684.1832 4341.5878)
      (2676.3969 4342.8244) (2668.6107 4341.5878) (2661.5878 4338.0153) (2656.0153 4332.4427) (2652.4427 4325.4198)
    ))
    ; P2852 -- see feature_dimensions_mm.csv
    ("06_ORNAMENT" 1 (
      (2651.2061 3926.6412) (2652.4427 3918.855) (2656.0153 3911.8321) (2661.5878 3906.2595) (2668.6107 3902.687)
      (2676.3969 3901.4504) (2684.1832 3902.687) (2691.2061 3906.2595) (2696.7786 3911.8321) (2700.3511 3918.855)
      (2701.5878 3926.6412) (2700.3511 3934.4275) (2696.7786 3941.4504) (2691.2061 3947.0229) (2684.1832 3950.5954)
      (2676.3969 3951.8321) (2668.6107 3950.5954) (2661.5878 3947.0229) (2656.0153 3941.4504) (2652.4427 3934.4275)
    ))
    ; P2853 -- see feature_dimensions_mm.csv
    ("06_ORNAMENT" 1 (
      (2668.4733 5312.9771) (2669.1908 5307.8473) (2671.313 5302.855) (2674.7939 5298.1069) (2679.542 5293.7252)
      (2685.4504 5289.8168) (2692.3511 5286.4885) (2700.1069 5283.8015) (2708.5038 5281.8321) (2717.3435 5280.626)
      (2726.4122 5280.229) (2735.4809 5280.626) (2744.3206 5281.8321) (2752.7176 5283.8015) (2760.4733 5286.4885)
      (2767.374 5289.8168) (2773.2824 5293.7252) (2778.0305 5298.1069) (2781.5115 5302.855) (2783.6336 5307.8473)
      (2784.3511 5312.9771) (2783.6336 5318.1069) (2781.5115 5323.0992) (2778.0305 5327.8473) (2773.2824 5332.229)
      (2767.374 5336.1374) (2760.4733 5339.4656) (2752.7176 5342.1527) (2744.3206 5344.1221) (2735.4809 5345.3282)
      (2726.4122 5345.7252) (2717.3435 5345.3282) (2708.5038 5344.1221) (2700.1069 5342.1527) (2692.3511 5339.4656)
      (2685.4504 5336.1374) (2679.542 5332.229) (2674.7939 5327.8473) (2671.313 5323.0992) (2669.1908 5318.1069)
    ))
    ; P2854 -- see feature_dimensions_mm.csv
    ("06_ORNAMENT" 1 (
      (2668.4733 4717.5573) (2669.1908 4712.4275) (2671.313 4707.4351) (2674.7939 4702.687) (2679.542 4698.3053)
      (2685.4504 4694.3969) (2692.3511 4691.0687) (2700.1069 4688.3817) (2708.5038 4686.4122) (2717.3435 4685.2061)
      (2726.4122 4684.8092) (2735.4809 4685.2061) (2744.3206 4686.4122) (2752.7176 4688.3817) (2760.4733 4691.0687)
      (2767.374 4694.3969) (2773.2824 4698.3053) (2778.0305 4702.687) (2781.5115 4707.4351) (2783.6336 4712.4275)
      (2784.3511 4717.5573) (2783.6336 4722.687) (2781.5115 4727.6794) (2778.0305 4732.4275) (2773.2824 4736.8092)
      (2767.374 4740.7176) (2760.4733 4744.0458) (2752.7176 4746.7328) (2744.3206 4748.7023) (2735.4809 4749.9084)
      (2726.4122 4750.3053) (2717.3435 4749.9084) (2708.5038 4748.7023) (2700.1069 4746.7328) (2692.3511 4744.0458)
      (2685.4504 4740.7176) (2679.542 4736.8092) (2674.7939 4732.4275) (2671.313 4727.6794) (2669.1908 4722.687)
    ))
    ; P2855 -- see feature_dimensions_mm.csv
    ("06_ORNAMENT" 1 (
      (2668.4733 4122.1374) (2669.1908 4117.0076) (2671.313 4112.0153) (2674.7939 4107.2672) (2679.542 4102.8855)
      (2685.4504 4098.9771) (2692.3511 4095.6489) (2700.1069 4092.9618) (2708.5038 4090.9924) (2717.3435 4089.7863)
      (2726.4122 4089.3893) (2735.4809 4089.7863) (2744.3206 4090.9924) (2752.7176 4092.9618) (2760.4733 4095.6489)
      (2767.374 4098.9771) (2773.2824 4102.8855) (2778.0305 4107.2672) (2781.5115 4112.0153) (2783.6336 4117.0076)
      (2784.3511 4122.1374) (2783.6336 4127.2672) (2781.5115 4132.2595) (2778.0305 4137.0076) (2773.2824 4141.3893)
      (2767.374 4145.2977) (2760.4733 4148.626) (2752.7176 4151.313) (2744.3206 4153.2824) (2735.4809 4154.4885)
      (2726.4122 4154.8855) (2717.3435 4154.4885) (2708.5038 4153.2824) (2700.1069 4151.313) (2692.3511 4148.626)
      (2685.4504 4145.2977) (2679.542 4141.3893) (2674.7939 4137.0076) (2671.313 4132.2595) (2669.1908 4127.2672)
    ))
    ; P2856 -- see feature_dimensions_mm.csv
    ("06_ORNAMENT" 1 (
      (2685.2977 5068.6107) (2686.8244 5062.9466) (2690.9771 5058.7939) (2696.6412 5057.2672) (2702.3053 5058.7939)
      (2706.458 5062.9466) (2707.9695 5068.6107) (2706.458 5074.2748) (2702.3053 5078.4275) (2696.6412 5079.9389)
      (2690.9771 5078.4275) (2686.8244 5074.2748)
    ))
    ; P2857 -- see feature_dimensions_mm.csv
    ("06_ORNAMENT" 1 (
      (2685.2977 4961.9237) (2686.8244 4956.2595) (2690.9771 4952.1069) (2696.6412 4950.5954) (2702.3053 4952.1069)
      (2706.458 4956.2595) (2707.9695 4961.9237) (2706.458 4967.5878) (2702.3053 4971.7405) (2696.6412 4973.2672)
      (2690.9771 4971.7405) (2686.8244 4967.5878)
    ))
    ; P2858 -- see feature_dimensions_mm.csv
    ("06_ORNAMENT" 1 (
      (2685.2977 4366.5038) (2686.8244 4360.8397) (2690.9771 4356.687) (2696.6412 4355.1756) (2702.3053 4356.687)
      (2706.458 4360.8397) (2707.9695 4366.5038) (2706.458 4372.1679) (2702.3053 4376.3206) (2696.6412 4377.8473)
      (2690.9771 4376.3206) (2686.8244 4372.1679)
    ))
    ; P2859 -- see feature_dimensions_mm.csv
    ("06_ORNAMENT" 1 (
      (2685.2977 3877.771) (2686.8244 3872.1069) (2690.9771 3867.9542) (2696.6412 3866.4275) (2702.3053 3867.9542)
      (2706.458 3872.1069) (2707.9695 3877.771) (2706.458 3883.4351) (2702.3053 3887.5878) (2696.6412 3889.0992)
      (2690.9771 3887.5878) (2686.8244 3883.4351)
    ))
    ; P2860 -- see feature_dimensions_mm.csv
    ("06_ORNAMENT" 1 (
      (2693.1298 5022.9008) (2693.542 5020.3206) (2694.7328 5017.8931) (2696.626 5015.6947) (2699.084 5013.8626)
      (2701.9237 5012.4122) (2704.9466 5011.3588) (2707.9847 5010.6412) (2710.8244 5010.1985) (2713.3435 5009.8779)
      (2715.4351 5009.5573) (2717.0687 5009.084) (2718.229 5008.3053) (2719.0076 5007.145) (2719.4809 5005.5115)
      (2719.8015 5003.4198) (2720.1221 5000.9008) (2720.5649 4998.0611) (2721.2824 4995.0229) (2722.3359 4992.0)
      (2723.7863 4989.1603) (2725.6183 4986.7023) (2727.8168 4984.8092) (2730.2443 4983.6183) (2732.8244 4983.2061)
      (2735.4046 4983.6183) (2737.8321 4984.8092) (2740.0305 4986.7023) (2741.8626 4989.1603) (2743.313 4992.0)
      (2744.3664 4995.0229) (2745.084 4998.0611) (2745.5267 5000.9008) (2745.8473 5003.4198) (2746.1679 5005.5115)
      (2746.6412 5007.145) (2747.4198 5008.3053) (2748.5802 5009.084) (2750.2137 5009.5573) (2752.3053 5009.8779)
      (2754.8244 5010.1985) (2757.6641 5010.6412) (2760.7023 5011.3588) (2763.7252 5012.4122) (2766.5649 5013.8626)
      (2769.0229 5015.6947) (2770.916 5017.8931) (2772.1069 5020.3206) (2772.5191 5022.9008) (2772.1069 5025.4809)
      (2770.916 5027.9084) (2769.0229 5030.1069) (2766.5649 5031.9389) (2763.7252 5033.3893) (2760.7023 5034.4427)
      (2757.6641 5035.1603) (2754.8244 5035.6031) (2752.3053 5035.9237) (2750.2137 5036.2443) (2748.5802 5036.7176)
      (2747.4198 5037.4962) (2746.6412 5038.6565) (2746.1679 5040.2901) (2745.8473 5042.3817) (2745.5267 5044.9008)
      (2745.084 5047.7405) (2744.3664 5050.7786) (2743.313 5053.8015) (2741.8626 5056.6412) (2740.0305 5059.0992)
      (2737.8321 5060.9924) (2735.4046 5062.1832) (2732.8244 5062.5954) (2730.2443 5062.1832) (2727.8168 5060.9924)
      (2725.6183 5059.0992) (2723.7863 5056.6412) (2722.3359 5053.8015) (2721.2824 5050.7786) (2720.5649 5047.7405)
      (2720.1221 5044.9008) (2719.8015 5042.3817) (2719.4809 5040.2901) (2719.0076 5038.6565) (2718.229 5037.4962)
      (2717.0687 5036.7176) (2715.4351 5036.2443) (2713.3435 5035.9237) (2710.8244 5035.6031) (2707.9847 5035.1603)
      (2704.9466 5034.4427) (2701.9237 5033.3893) (2699.084 5031.9389) (2696.626 5030.1069) (2694.7328 5027.9084)
      (2693.542 5025.4809)
    ))
    ; P2861 -- see feature_dimensions_mm.csv
    ("06_ORNAMENT" 1 (
      (2702.2901 6137.4046) (2711.1603 6122.0153) (2721.8015 6105.771) (2734.0 6088.9313) (2747.6031 6071.7557)
      (2762.4427 6054.5191) (2778.3206 6037.4656) (2795.084 6020.855) (2812.5496 6004.9466) (2830.5191 5990.0153)
      (2848.855 5976.3053) (2867.3588 5964.0916) (2885.8473 5953.6031) (2904.1679 5945.1298) (2922.1374 5938.9313)
      (2913.2214 5956.9924) (2902.1069 5975.0992) (2889.0687 5993.084) (2874.4122 6010.8092) (2858.4122 6028.0763)
      (2841.374 6044.7634) (2823.5725 6060.687) (2805.313 6075.6947) (2786.8855 6089.6336) (2768.5649 6102.3053)
      (2750.6565 6113.5878) (2733.4504 6123.313) (2717.2214 6131.2977)
    ))
    ; P2862 -- see feature_dimensions_mm.csv
    ("06_ORNAMENT" 1 (
      (2708.3969 7374.0458) (2709.7557 7371.5267) (2713.4656 7369.4809) (2718.5038 7368.1527) (2723.5573 7367.4656)
      (2727.3435 7367.0076) (2729.0229 7366.1527) (2728.4275 7364.3511) (2726.0916 7361.3435) (2723.0076 7357.2824)
      (2720.3817 7352.7786) (2719.2061 7348.7176) (2720.0305 7345.9847) (2722.7634 7345.1603) (2726.8244 7346.3359)
      (2731.3282 7348.9618) (2735.3893 7352.0458) (2738.3969 7354.3817) (2740.1985 7354.9771) (2741.0534 7353.2977)
      (2741.5115 7349.5115) (2742.2137 7344.458) (2743.5267 7339.4198) (2745.5725 7335.7099) (2748.0916 7334.3511)
      (2750.6107 7335.7099) (2752.6565 7339.4198) (2753.9847 7344.458) (2754.6718 7349.5115) (2755.1298 7353.2977)
      (2755.9847 7354.9771) (2757.7863 7354.3817) (2760.7939 7352.0458) (2764.855 7348.9618) (2769.3588 7346.3359)
      (2773.4198 7345.1603) (2776.1527 7345.9847) (2776.9771 7348.7176) (2775.8015 7352.7786) (2773.1756 7357.2824)
      (2770.0916 7361.3435) (2767.7557 7364.3511) (2767.1603 7366.1527) (2768.8397 7367.0076) (2772.626 7367.4656)
      (2777.6794 7368.1527) (2782.7176 7369.4809) (2786.4275 7371.5267) (2787.7863 7374.0458) (2786.4275 7376.5649)
      (2782.7176 7378.6107) (2777.6794 7379.9237) (2772.626 7380.626) (2768.8397 7381.084) (2767.1603 7381.9389)
      (2767.7557 7383.7405) (2770.0916 7386.7481) (2773.1756 7390.8092) (2775.8015 7395.313) (2776.9771 7399.374)
      (2776.1527 7402.1069) (2773.4198 7402.9313) (2769.3588 7401.7557) (2764.855 7399.1298) (2760.7939 7396.0458)
      (2757.7863 7393.7099) (2755.9847 7393.1145) (2755.1298 7394.7939) (2754.6718 7398.5802) (2753.9847 7403.6336)
      (2752.6565 7408.6718) (2750.6107 7412.3817) (2748.0916 7413.7405) (2745.5725 7412.3817) (2743.5267 7408.6718)
      (2742.2137 7403.6336) (2741.5115 7398.5802) (2741.0534 7394.7939) (2740.1985 7393.1145) (2738.3969 7393.7099)
      (2735.3893 7396.0458) (2731.3282 7399.1298) (2726.8244 7401.7557) (2722.7634 7402.9313) (2720.0305 7402.1069)
      (2719.2061 7399.374) (2720.3817 7395.313) (2723.0076 7390.8092) (2726.0916 7386.7481) (2728.4275 7383.7405)
      (2729.0229 7381.9389) (2727.3435 7381.084) (2723.5573 7380.626) (2718.5038 7379.9237) (2713.4656 7378.6107)
      (2709.7557 7376.5649)
    ))
    ; P2863 -- see feature_dimensions_mm.csv
    ("06_ORNAMENT" 1 (
      (2708.3969 7206.1069) (2709.7557 7203.5878) (2713.4656 7201.542) (2718.5038 7200.2137) (2723.5573 7199.5267)
      (2727.3435 7199.0687) (2729.0229 7198.2137) (2728.4275 7196.4122) (2726.0916 7193.4046) (2723.0076 7189.3435)
      (2720.3817 7184.8397) (2719.2061 7180.7786) (2720.0305 7178.0458) (2722.7634 7177.2214) (2726.8244 7178.3969)
      (2731.3282 7181.0229) (2735.3893 7184.1069) (2738.3969 7186.4427) (2740.1985 7187.0382) (2741.0534 7185.3588)
      (2741.5115 7181.5725) (2742.2137 7176.5191) (2743.5267 7171.4809) (2745.5725 7167.771) (2748.0916 7166.4122)
      (2750.6107 7167.771) (2752.6565 7171.4809) (2753.9847 7176.5191) (2754.6718 7181.5725) (2755.1298 7185.3588)
      (2755.9847 7187.0382) (2757.7863 7186.4427) (2760.7939 7184.1069) (2764.855 7181.0229) (2769.3588 7178.3969)
      (2773.4198 7177.2214) (2776.1527 7178.0458) (2776.9771 7180.7786) (2775.8015 7184.8397) (2773.1756 7189.3435)
      (2770.0916 7193.4046) (2767.7557 7196.4122) (2767.1603 7198.2137) (2768.8397 7199.0687) (2772.626 7199.5267)
      (2777.6794 7200.2137) (2782.7176 7201.542) (2786.4275 7203.5878) (2787.7863 7206.1069) (2786.4275 7208.626)
      (2782.7176 7210.6718) (2777.6794 7211.9847) (2772.626 7212.687) (2768.8397 7213.145) (2767.1603 7214.0)
      (2767.7557 7215.8015) (2770.0916 7218.8092) (2773.1756 7222.8702) (2775.8015 7227.374) (2776.9771 7231.4351)
      (2776.1527 7234.1679) (2773.4198 7234.9924) (2769.3588 7233.8168) (2764.855 7231.1908) (2760.7939 7228.1069)
      (2757.7863 7225.771) (2755.9847 7225.1756) (2755.1298 7226.855) (2754.6718 7230.6412) (2753.9847 7235.6947)
      (2752.6565 7240.7328) (2750.6107 7244.4427) (2748.0916 7245.8015) (2745.5725 7244.4427) (2743.5267 7240.7328)
      (2742.2137 7235.6947) (2741.5115 7230.6412) (2741.0534 7226.855) (2740.1985 7225.1756) (2738.3969 7225.771)
      (2735.3893 7228.1069) (2731.3282 7231.1908) (2726.8244 7233.8168) (2722.7634 7234.9924) (2720.0305 7234.1679)
      (2719.2061 7231.4351) (2720.3817 7227.374) (2723.0076 7222.8702) (2726.0916 7218.8092) (2728.4275 7215.8015)
      (2729.0229 7214.0) (2727.3435 7213.145) (2723.5573 7212.687) (2718.5038 7211.9847) (2713.4656 7210.6718)
      (2709.7557 7208.626)
    ))
    ; P2864 -- see feature_dimensions_mm.csv
    ("06_ORNAMENT" 1 (
      (2738.9618 7374.0458) (2739.6641 7370.5496) (2741.6336 7367.5878) (2744.5954 7365.6183) (2748.0916 7364.916)
      (2751.5878 7365.6183) (2754.5496 7367.5878) (2756.5191 7370.5496) (2757.2214 7374.0458) (2756.5191 7377.542)
      (2754.5496 7380.5038) (2751.5878 7382.4733) (2748.0916 7383.1756) (2744.5954 7382.4733) (2741.6336 7380.5038)
      (2739.6641 7377.542)
    ))
    ; P2865 -- see feature_dimensions_mm.csv
    ("06_ORNAMENT" 1 (
      (2738.9618 7206.1069) (2739.6641 7202.6107) (2741.6336 7199.6489) (2744.5954 7197.6794) (2748.0916 7196.9771)
      (2751.5878 7197.6794) (2754.5496 7199.6489) (2756.5191 7202.6107) (2757.2214 7206.1069) (2756.5191 7209.6031)
      (2754.5496 7212.5649) (2751.5878 7214.5344) (2748.0916 7215.2366) (2744.5954 7214.5344) (2741.6336 7212.5649)
      (2739.6641 7209.6031)
    ))
    ; P2866 -- see feature_dimensions_mm.csv
    ("06_ORNAMENT" 1 (
      (2765.7252 5393.9542) (2766.9618 5386.1679) (2770.5344 5379.145) (2776.1069 5373.5725) (2783.1298 5370.0)
      (2790.916 5368.7634) (2798.7023 5370.0) (2805.7252 5373.5725) (2811.2977 5379.145) (2814.8702 5386.1679)
      (2816.1069 5393.9542) (2814.8702 5401.7405) (2811.2977 5408.7634) (2805.7252 5414.3359) (2798.7023 5417.9084)
      (2790.916 5419.145) (2783.1298 5417.9084) (2776.1069 5414.3359) (2770.5344 5408.7634) (2766.9618 5401.7405)
    ))
    ; P2867 -- see feature_dimensions_mm.csv
    ("06_ORNAMENT" 1 (
      (2765.7252 5232.0) (2766.9618 5224.2137) (2770.5344 5217.1908) (2776.1069 5211.6183) (2783.1298 5208.0458)
      (2790.916 5206.8092) (2798.7023 5208.0458) (2805.7252 5211.6183) (2811.2977 5217.1908) (2814.8702 5224.2137)
      (2816.1069 5232.0) (2814.8702 5239.7863) (2811.2977 5246.8092) (2805.7252 5252.3817) (2798.7023 5255.9542)
      (2790.916 5257.1908) (2783.1298 5255.9542) (2776.1069 5252.3817) (2770.5344 5246.8092) (2766.9618 5239.7863)
    ))
    ; P2868 -- see feature_dimensions_mm.csv
    ("06_ORNAMENT" 1 (
      (2765.7252 4798.5344) (2766.9618 4790.7481) (2770.5344 4783.7252) (2776.1069 4778.1527) (2783.1298 4774.5802)
      (2790.916 4773.3435) (2798.7023 4774.5802) (2805.7252 4778.1527) (2811.2977 4783.7252) (2814.8702 4790.7481)
      (2816.1069 4798.5344) (2814.8702 4806.3206) (2811.2977 4813.3435) (2805.7252 4818.916) (2798.7023 4822.4885)
      (2790.916 4823.7252) (2783.1298 4822.4885) (2776.1069 4818.916) (2770.5344 4813.3435) (2766.9618 4806.3206)
    ))
    ; P2869 -- see feature_dimensions_mm.csv
    ("06_ORNAMENT" 1 (
      (2765.7252 4636.5802) (2766.9618 4628.7939) (2770.5344 4621.771) (2776.1069 4616.1985) (2783.1298 4612.626)
      (2790.916 4611.3893) (2798.7023 4612.626) (2805.7252 4616.1985) (2811.2977 4621.771) (2814.8702 4628.7939)
      (2816.1069 4636.5802) (2814.8702 4644.3664) (2811.2977 4651.3893) (2805.7252 4656.9618) (2798.7023 4660.5344)
      (2790.916 4661.771) (2783.1298 4660.5344) (2776.1069 4656.9618) (2770.5344 4651.3893) (2766.9618 4644.3664)
    ))
    ; P2870 -- see feature_dimensions_mm.csv
    ("06_ORNAMENT" 1 (
      (2765.7252 4203.1145) (2766.9618 4195.3282) (2770.5344 4188.3053) (2776.1069 4182.7328) (2783.1298 4179.1603)
      (2790.916 4177.9237) (2798.7023 4179.1603) (2805.7252 4182.7328) (2811.2977 4188.3053) (2814.8702 4195.3282)
      (2816.1069 4203.1145) (2814.8702 4210.9008) (2811.2977 4217.9237) (2805.7252 4223.4962) (2798.7023 4227.0687)
      (2790.916 4228.3053) (2783.1298 4227.0687) (2776.1069 4223.4962) (2770.5344 4217.9237) (2766.9618 4210.9008)
    ))
    ; P2871 -- see feature_dimensions_mm.csv
    ("06_ORNAMENT" 1 (
      (2765.7252 4041.1603) (2766.9618 4033.374) (2770.5344 4026.3511) (2776.1069 4020.7786) (2783.1298 4017.2061)
      (2790.916 4015.9695) (2798.7023 4017.2061) (2805.7252 4020.7786) (2811.2977 4026.3511) (2814.8702 4033.374)
      (2816.1069 4041.1603) (2814.8702 4048.9466) (2811.2977 4055.9695) (2805.7252 4061.542) (2798.7023 4065.1145)
      (2790.916 4066.3511) (2783.1298 4065.1145) (2776.1069 4061.542) (2770.5344 4055.9695) (2766.9618 4048.9466)
    ))
    ; P2872 -- see feature_dimensions_mm.csv
    ("06_ORNAMENT" 1 (
      (2771.1145 5500.0153) (2772.6412 5494.3359) (2776.7786 5490.1985) (2782.458 5488.6718) (2788.1221 5490.1985)
      (2792.2748 5494.3359) (2793.7863 5500.0153) (2792.2748 5505.6794) (2788.1221 5509.8321) (2782.458 5511.3435)
      (2776.7786 5509.8321) (2772.6412 5505.6794)
    ))
    ; P2873 -- see feature_dimensions_mm.csv
    ("06_ORNAMENT" 1 (
      (2771.1145 5125.9389) (2772.6412 5120.2748) (2776.7786 5116.1221) (2782.458 5114.6107) (2788.1221 5116.1221)
      (2792.2748 5120.2748) (2793.7863 5125.9389) (2792.2748 5131.6183) (2788.1221 5135.7557) (2782.458 5137.2824)
      (2776.7786 5135.7557) (2772.6412 5131.6183)
    ))
    ; P2874 -- see feature_dimensions_mm.csv
    ("06_ORNAMENT" 1 (
      (2771.1145 4904.5954) (2772.6412 4898.916) (2776.7786 4894.7786) (2782.458 4893.2519) (2788.1221 4894.7786)
      (2792.2748 4898.916) (2793.7863 4904.5954) (2792.2748 4910.2595) (2788.1221 4914.4122) (2782.458 4915.9237)
      (2776.7786 4914.4122) (2772.6412 4910.2595)
    ))
    ; P2875 -- see feature_dimensions_mm.csv
    ("06_ORNAMENT" 1 (
      (2771.1145 4530.5191) (2772.6412 4524.855) (2776.7786 4520.7023) (2782.458 4519.1908) (2788.1221 4520.7023)
      (2792.2748 4524.855) (2793.7863 4530.5191) (2792.2748 4536.1985) (2788.1221 4540.3359) (2782.458 4541.8626)
      (2776.7786 4540.3359) (2772.6412 4536.1985)
    ))
    ; P2876 -- see feature_dimensions_mm.csv
    ("06_ORNAMENT" 1 (
      (2771.1145 4309.1756) (2772.6412 4303.4962) (2776.7786 4299.3588) (2782.458 4297.8321) (2788.1221 4299.3588)
      (2792.2748 4303.4962) (2793.7863 4309.1756) (2792.2748 4314.8397) (2788.1221 4318.9924) (2782.458 4320.5038)
      (2776.7786 4318.9924) (2772.6412 4314.8397)
    ))
    ; P2877 -- see feature_dimensions_mm.csv
    ("06_ORNAMENT" 1 (
      (2771.1145 3935.0992) (2772.6412 3929.4351) (2776.7786 3925.2824) (2782.458 3923.771) (2788.1221 3925.2824)
      (2792.2748 3929.4351) (2793.7863 3935.0992) (2792.2748 3940.7786) (2788.1221 3944.916) (2782.458 3946.4427)
      (2776.7786 3944.916) (2772.6412 3940.7786)
    ))
    ; P2878 -- see feature_dimensions_mm.csv
    ("06_ORNAMENT" 1 (
      (2828.458 5414.1985) (2829.9695 5408.5344) (2834.1221 5404.3817) (2839.7863 5402.855) (2845.4504 5404.3817)
      (2849.6031 5408.5344) (2851.1298 5414.1985) (2849.6031 5419.8626) (2845.4504 5424.0153) (2839.7863 5425.5267)
      (2834.1221 5424.0153) (2829.9695 5419.8626)
    ))
    ; P2879 -- see feature_dimensions_mm.csv
    ("06_ORNAMENT" 1 (
      (2828.458 5211.7557) (2829.9695 5206.0916) (2834.1221 5201.9389) (2839.7863 5200.4275) (2845.4504 5201.9389)
      (2849.6031 5206.0916) (2851.1298 5211.7557) (2849.6031 5217.4198) (2845.4504 5221.5725) (2839.7863 5223.0992)
      (2834.1221 5221.5725) (2829.9695 5217.4198)
    ))
    ; P2880 -- see feature_dimensions_mm.csv
    ("06_ORNAMENT" 1 (
      (2828.458 4818.7786) (2829.9695 4813.1145) (2834.1221 4808.9618) (2839.7863 4807.4351) (2845.4504 4808.9618)
      (2849.6031 4813.1145) (2851.1298 4818.7786) (2849.6031 4824.4427) (2845.4504 4828.5954) (2839.7863 4830.1069)
      (2834.1221 4828.5954) (2829.9695 4824.4427)
    ))
    ; P2881 -- see feature_dimensions_mm.csv
    ("06_ORNAMENT" 1 (
      (2828.458 4616.3359) (2829.9695 4610.6718) (2834.1221 4606.5191) (2839.7863 4605.0076) (2845.4504 4606.5191)
      (2849.6031 4610.6718) (2851.1298 4616.3359) (2849.6031 4622.0) (2845.4504 4626.1527) (2839.7863 4627.6794)
      (2834.1221 4626.1527) (2829.9695 4622.0)
    ))
    ; P2882 -- see feature_dimensions_mm.csv
    ("06_ORNAMENT" 1 (
      (2828.458 4223.3588) (2829.9695 4217.6947) (2834.1221 4213.542) (2839.7863 4212.0153) (2845.4504 4213.542)
      (2849.6031 4217.6947) (2851.1298 4223.3588) (2849.6031 4229.0229) (2845.4504 4233.1756) (2839.7863 4234.687)
      (2834.1221 4233.1756) (2829.9695 4229.0229)
    ))
    ; P2883 -- see feature_dimensions_mm.csv
    ("06_ORNAMENT" 1 (
      (2828.458 4020.916) (2829.9695 4015.2519) (2834.1221 4011.0992) (2839.7863 4009.5878) (2845.4504 4011.0992)
      (2849.6031 4015.2519) (2851.1298 4020.916) (2849.6031 4026.5802) (2845.4504 4030.7328) (2839.7863 4032.2595)
      (2834.1221 4030.7328) (2829.9695 4026.5802)
    ))
    ; P2884 -- see feature_dimensions_mm.csv
    ("06_ORNAMENT" 1 (
      (2839.6947 6183.2061) (2840.9771 6167.0229) (2843.4351 6149.5115) (2847.0534 6130.9618) (2851.7557 6111.6489)
      (2857.5267 6091.8626) (2864.3053 6071.8931) (2872.0611 6052.0) (2880.7176 6032.4885) (2890.2748 6013.6183)
      (2900.6565 5995.6794) (2911.8168 5978.9618) (2923.7405 5963.7557) (2936.3511 5950.3053) (2949.6183 5938.9313)
      (2949.4504 5957.4198) (2947.3435 5976.687) (2943.4962 5996.5038) (2938.0763 6016.6412) (2931.2977 6036.8397)
      (2923.3282 6056.9008) (2914.3664 6076.5496) (2904.6107 6095.5725) (2894.229 6113.7252) (2883.4198 6130.7786)
      (2872.3817 6146.4885) (2861.2824 6160.6107) (2850.3206 6172.9313)
    ))
    ; P2885 -- see feature_dimensions_mm.csv
    ("06_ORNAMENT" 1 (
      (2848.5954 5312.9771) (2850.1069 5307.313) (2854.2595 5303.1603) (2859.9237 5301.6336) (2865.5878 5303.1603)
      (2869.7405 5307.313) (2871.2672 5312.9771) (2869.7405 5318.6412) (2865.5878 5322.7939) (2859.9237 5324.3053)
      (2854.2595 5322.7939) (2850.1069 5318.6412)
    ))
    ; P2886 -- see feature_dimensions_mm.csv
    ("06_ORNAMENT" 1 (
      (2848.5954 4717.5573) (2850.1069 4711.8931) (2854.2595 4707.7405) (2859.9237 4706.2137) (2865.5878 4707.7405)
      (2869.7405 4711.8931) (2871.2672 4717.5573) (2869.7405 4723.2214) (2865.5878 4727.374) (2859.9237 4728.8855)
      (2854.2595 4727.374) (2850.1069 4723.2214)
    ))
    ; P2887 -- see feature_dimensions_mm.csv
    ("06_ORNAMENT" 1 (
      (2848.5954 4122.1374) (2850.1069 4116.4733) (2854.2595 4112.3206) (2859.9237 4110.7939) (2865.5878 4112.3206)
      (2869.7405 4116.4733) (2871.2672 4122.1374) (2869.7405 4127.8015) (2865.5878 4131.9542) (2859.9237 4133.4656)
      (2854.2595 4131.9542) (2850.1069 4127.8015)
    ))
    ; P2888 -- see feature_dimensions_mm.csv
    ("06_ORNAMENT" 1 (
      (2878.626 5504.0763) (2879.8473 5497.9389) (2883.3282 5492.7328) (2888.5191 5489.2672) (2894.6565 5488.0458)
      (2900.7939 5489.2672) (2905.9847 5492.7328) (2909.4656 5497.9389) (2910.687 5504.0763) (2909.4656 5510.2137)
      (2905.9847 5515.4046) (2900.7939 5518.8855) (2894.6565 5520.1069) (2888.5191 5518.8855) (2883.3282 5515.4046)
      (2879.8473 5510.2137)
    ))
    ; P2889 -- see feature_dimensions_mm.csv
    ("06_ORNAMENT" 1 (
      (2878.626 5427.7405) (2879.8473 5421.6031) (2883.3282 5416.3969) (2888.5191 5412.9313) (2894.6565 5411.7099)
      (2900.7939 5412.9313) (2905.9847 5416.3969) (2909.4656 5421.6031) (2910.687 5427.7405) (2909.4656 5433.8779)
      (2905.9847 5439.0687) (2900.7939 5442.5496) (2894.6565 5443.771) (2888.5191 5442.5496) (2883.3282 5439.0687)
      (2879.8473 5433.8779)
    ))
    ; P2890 -- see feature_dimensions_mm.csv
    ("06_ORNAMENT" 1 (
      (2878.626 5351.4046) (2879.8473 5345.2672) (2883.3282 5340.0611) (2888.5191 5336.5954) (2894.6565 5335.374)
      (2900.7939 5336.5954) (2905.9847 5340.0611) (2909.4656 5345.2672) (2910.687 5351.4046) (2909.4656 5357.542)
      (2905.9847 5362.7328) (2900.7939 5366.2137) (2894.6565 5367.4351) (2888.5191 5366.2137) (2883.3282 5362.7328)
      (2879.8473 5357.542)
    ))
    ; P2891 -- see feature_dimensions_mm.csv
    ("06_ORNAMENT" 1 (
      (2878.626 5275.0687) (2879.8473 5268.9313) (2883.3282 5263.7252) (2888.5191 5260.2595) (2894.6565 5259.0382)
      (2900.7939 5260.2595) (2905.9847 5263.7252) (2909.4656 5268.9313) (2910.687 5275.0687) (2909.4656 5281.2061)
      (2905.9847 5286.3969) (2900.7939 5289.8779) (2894.6565 5291.0992) (2888.5191 5289.8779) (2883.3282 5286.3969)
      (2879.8473 5281.2061)
    ))
    ; P2892 -- see feature_dimensions_mm.csv
    ("06_ORNAMENT" 1 (
      (2878.626 5198.7328) (2879.8473 5192.5954) (2883.3282 5187.3893) (2888.5191 5183.9237) (2894.6565 5182.7023)
      (2900.7939 5183.9237) (2905.9847 5187.3893) (2909.4656 5192.5954) (2910.687 5198.7328) (2909.4656 5204.8702)
      (2905.9847 5210.0611) (2900.7939 5213.542) (2894.6565 5214.7634) (2888.5191 5213.542) (2883.3282 5210.0611)
      (2879.8473 5204.8702)
    ))
    ; P2893 -- see feature_dimensions_mm.csv
    ("06_ORNAMENT" 1 (
      (2878.626 5122.3969) (2879.8473 5116.2595) (2883.3282 5111.0534) (2888.5191 5107.5878) (2894.6565 5106.3664)
      (2900.7939 5107.5878) (2905.9847 5111.0534) (2909.4656 5116.2595) (2910.687 5122.3969) (2909.4656 5128.5344)
      (2905.9847 5133.7252) (2900.7939 5137.2061) (2894.6565 5138.4275) (2888.5191 5137.2061) (2883.3282 5133.7252)
      (2879.8473 5128.5344)
    ))
    ; P2894 -- see feature_dimensions_mm.csv
    ("06_ORNAMENT" 1 (
      (2878.626 5046.0611) (2879.8473 5039.9237) (2883.3282 5034.7176) (2888.5191 5031.2519) (2894.6565 5030.0305)
      (2900.7939 5031.2519) (2905.9847 5034.7176) (2909.4656 5039.9237) (2910.687 5046.0611) (2909.4656 5052.1985)
      (2905.9847 5057.3893) (2900.7939 5060.8702) (2894.6565 5062.0916) (2888.5191 5060.8702) (2883.3282 5057.3893)
      (2879.8473 5052.1985)
    ))
    ; P2895 -- see feature_dimensions_mm.csv
    ("06_ORNAMENT" 1 (
      (2878.626 4969.7252) (2879.8473 4963.5878) (2883.3282 4958.3817) (2888.5191 4954.916) (2894.6565 4953.6947)
      (2900.7939 4954.916) (2905.9847 4958.3817) (2909.4656 4963.5878) (2910.687 4969.7252) (2909.4656 4975.8626)
      (2905.9847 4981.0534) (2900.7939 4984.5344) (2894.6565 4985.7557) (2888.5191 4984.5344) (2883.3282 4981.0534)
      (2879.8473 4975.8626)
    ))
    ; P2896 -- see feature_dimensions_mm.csv
    ("06_ORNAMENT" 1 (
      (2878.626 4893.3893) (2879.8473 4887.2519) (2883.3282 4882.0458) (2888.5191 4878.5802) (2894.6565 4877.3588)
      (2900.7939 4878.5802) (2905.9847 4882.0458) (2909.4656 4887.2519) (2910.687 4893.3893) (2909.4656 4899.5267)
      (2905.9847 4904.7176) (2900.7939 4908.1985) (2894.6565 4909.4198) (2888.5191 4908.1985) (2883.3282 4904.7176)
      (2879.8473 4899.5267)
    ))
    ; P2897 -- see feature_dimensions_mm.csv
    ("06_ORNAMENT" 1 (
      (2878.626 4817.0534) (2879.8473 4810.916) (2883.3282 4805.7099) (2888.5191 4802.2443) (2894.6565 4801.0229)
      (2900.7939 4802.2443) (2905.9847 4805.7099) (2909.4656 4810.916) (2910.687 4817.0534) (2909.4656 4823.1908)
      (2905.9847 4828.3817) (2900.7939 4831.8626) (2894.6565 4833.084) (2888.5191 4831.8626) (2883.3282 4828.3817)
      (2879.8473 4823.1908)
    ))
    ; P2898 -- see feature_dimensions_mm.csv
    ("06_ORNAMENT" 1 (
      (2878.626 4664.3817) (2879.8473 4658.2443) (2883.3282 4653.0382) (2888.5191 4649.5725) (2894.6565 4648.3511)
      (2900.7939 4649.5725) (2905.9847 4653.0382) (2909.4656 4658.2443) (2910.687 4664.3817) (2909.4656 4670.5191)
      (2905.9847 4675.7099) (2900.7939 4679.1908) (2894.6565 4680.4122) (2888.5191 4679.1908) (2883.3282 4675.7099)
      (2879.8473 4670.5191)
    ))
    ; P2899 -- see feature_dimensions_mm.csv
    ("06_ORNAMENT" 1 (
      (2878.626 4588.0458) (2879.8473 4581.9084) (2883.3282 4576.7023) (2888.5191 4573.2366) (2894.6565 4572.0153)
      (2900.7939 4573.2366) (2905.9847 4576.7023) (2909.4656 4581.9084) (2910.687 4588.0458) (2909.4656 4594.1832)
      (2905.9847 4599.374) (2900.7939 4602.855) (2894.6565 4604.0763) (2888.5191 4602.855) (2883.3282 4599.374)
      (2879.8473 4594.1832)
    ))
    ; P2900 -- see feature_dimensions_mm.csv
    ("06_ORNAMENT" 1 (
      (2878.626 4511.7099) (2879.8473 4505.5725) (2883.3282 4500.3664) (2888.5191 4496.9008) (2894.6565 4495.6794)
      (2900.7939 4496.9008) (2905.9847 4500.3664) (2909.4656 4505.5725) (2910.687 4511.7099) (2909.4656 4517.8473)
      (2905.9847 4523.0382) (2900.7939 4526.5191) (2894.6565 4527.7405) (2888.5191 4526.5191) (2883.3282 4523.0382)
      (2879.8473 4517.8473)
    ))
    ; P2901 -- see feature_dimensions_mm.csv
    ("06_ORNAMENT" 1 (
      (2878.626 4359.0382) (2879.8473 4352.9008) (2883.3282 4347.6947) (2888.5191 4344.229) (2894.6565 4343.0076)
      (2900.7939 4344.229) (2905.9847 4347.6947) (2909.4656 4352.9008) (2910.687 4359.0382) (2909.4656 4365.1756)
      (2905.9847 4370.3664) (2900.7939 4373.8473) (2894.6565 4375.0687) (2888.5191 4373.8473) (2883.3282 4370.3664)
      (2879.8473 4365.1756)
    ))
    ; P2902 -- see feature_dimensions_mm.csv
    ("06_ORNAMENT" 1 (
      (2878.626 4282.7023) (2879.8473 4276.5649) (2883.3282 4271.3588) (2888.5191 4267.8931) (2894.6565 4266.6718)
      (2900.7939 4267.8931) (2905.9847 4271.3588) (2909.4656 4276.5649) (2910.687 4282.7023) (2909.4656 4288.8397)
      (2905.9847 4294.0305) (2900.7939 4297.5115) (2894.6565 4298.7328) (2888.5191 4297.5115) (2883.3282 4294.0305)
      (2879.8473 4288.8397)
    ))
    ; P2903 -- see feature_dimensions_mm.csv
    ("06_ORNAMENT" 1 (
      (2878.626 4206.3664) (2879.8473 4200.229) (2883.3282 4195.0229) (2888.5191 4191.5573) (2894.6565 4190.3359)
      (2900.7939 4191.5573) (2905.9847 4195.0229) (2909.4656 4200.229) (2910.687 4206.3664) (2909.4656 4212.5038)
      (2905.9847 4217.6947) (2900.7939 4221.1756) (2894.6565 4222.3969) (2888.5191 4221.1756) (2883.3282 4217.6947)
      (2879.8473 4212.5038)
    ))
    ; P2904 -- see feature_dimensions_mm.csv
    ("06_ORNAMENT" 1 (
      (2878.626 4053.6947) (2879.8473 4047.5573) (2883.3282 4042.3511) (2888.5191 4038.8855) (2894.6565 4037.6641)
      (2900.7939 4038.8855) (2905.9847 4042.3511) (2909.4656 4047.5573) (2910.687 4053.6947) (2909.4656 4059.8321)
      (2905.9847 4065.0229) (2900.7939 4068.5038) (2894.6565 4069.7252) (2888.5191 4068.5038) (2883.3282 4065.0229)
      (2879.8473 4059.8321)
    ))
    ; P2905 -- see feature_dimensions_mm.csv
    ("06_ORNAMENT" 1 (
      (2878.626 3977.3588) (2879.8473 3971.2214) (2883.3282 3966.0153) (2888.5191 3962.5496) (2894.6565 3961.3282)
      (2900.7939 3962.5496) (2905.9847 3966.0153) (2909.4656 3971.2214) (2910.687 3977.3588) (2909.4656 3983.4962)
      (2905.9847 3988.687) (2900.7939 3992.1679) (2894.6565 3993.3893) (2888.5191 3992.1679) (2883.3282 3988.687)
      (2879.8473 3983.4962)
    ))
    ; P2906 -- see feature_dimensions_mm.csv
    ("06_ORNAMENT" 1 (
      (2878.626 3901.0229) (2879.8473 3894.8855) (2883.3282 3889.6794) (2888.5191 3886.2137) (2894.6565 3884.9924)
      (2900.7939 3886.2137) (2905.9847 3889.6794) (2909.4656 3894.8855) (2910.687 3901.0229) (2909.4656 3907.1603)
      (2905.9847 3912.3511) (2900.7939 3915.8321) (2894.6565 3917.0534) (2888.5191 3915.8321) (2883.3282 3912.3511)
      (2879.8473 3907.1603)
    ))
    ; P2907 -- see feature_dimensions_mm.csv
    ("06_ORNAMENT" 1 (
      (2952.6565 6048.9771) (2953.6336 6028.5191) (2955.7405 6008.5496) (2959.0534 5989.3282) (2963.6794 5971.145)
      (2969.6641 5954.2595) (2977.0992 5938.9313) (2984.5344 5955.3282) (2990.5191 5973.1908) (2995.145 5992.2443)
      (2998.458 6012.1832) (3000.5649 6032.7328) (3001.542 6053.6183) (3001.4351 6074.5344) (3000.3359 6095.2366)
      (2998.3206 6115.4046) (2995.4656 6134.7634) (2991.8321 6153.0382) (2987.5115 6169.9237) (2982.5802 6185.1756)
      (2977.0992 6198.4733) (2971.6183 6183.6641) (2966.687 6167.2061) (2962.3664 6149.374) (2958.7328 6130.4427)
      (2955.8779 6110.6718) (2953.8626 6090.3206) (2952.7634 6069.6794)
    ))
    ; P2908 -- see feature_dimensions_mm.csv
    ("06_ORNAMENT" 1 (
      (3004.2901 5956.4122) (3004.5802 5938.9313) (3018.3053 5951.313) (3031.3282 5965.6641) (3043.6031 5981.6947)
      (3055.084 5999.0992) (3065.7099 6017.5878) (3075.4351 6036.8397) (3084.1985 6056.5802) (3091.9695 6076.5038)
      (3098.6718 6096.3053) (3104.2595 6115.7099) (3108.7023 6134.3969) (3111.9084 6152.0763) (3113.8626 6168.4427)
      (3114.5038 6183.2061) (3103.2366 6171.5115) (3091.771 6158.0458) (3080.2748 6143.0534) (3068.9466 6126.7176)
      (3057.9695 6109.2824) (3047.5115 6090.9618) (3037.771 6071.9695) (3028.9008 6052.5344) (3021.1145 6032.8855)
      (3014.5802 6013.2214) (3009.4809 5993.771) (3005.9847 5974.7634)
    ))
    ; P2909 -- see feature_dimensions_mm.csv
    ("06_ORNAMENT" 1 (
      (3032.0611 5938.9313) (3050.9313 5945.9542) (3070.0763 5955.1756) (3089.2977 5966.3053) (3108.4275 5979.084)
      (3127.2519 5993.2366) (3145.5725 6008.4885) (3163.2366 6024.5802) (3180.0305 6041.2061) (3195.7557 6058.1221)
      (3210.2443 6075.0534) (3223.2977 6091.7252) (3234.7176 6107.8473) (3244.3206 6123.1603) (3251.9084 6137.4046)
      (3235.6947 6130.1374) (3218.4427 6121.2214) (3200.458 6110.7939) (3181.9847 6099.0076) (3163.313 6086.0153)
      (3144.7328 6071.9542) (3126.5038 6056.9771) (3108.9008 6041.2214) (3092.2137 6024.855) (3076.7176 6008.0305)
      (3062.6718 5990.8702) (3050.3664 5973.5267) (3040.0611 5956.1679)
    ))
    ; P2910 -- see feature_dimensions_mm.csv
    ("06_ORNAMENT" 1 (
      (3043.5115 5504.0763) (3044.7328 5497.9389) (3048.2137 5492.7328) (3053.4046 5489.2672) (3059.542 5488.0458)
      (3065.6794 5489.2672) (3070.8702 5492.7328) (3074.3511 5497.9389) (3075.5725 5504.0763) (3074.3511 5510.2137)
      (3070.8702 5515.4046) (3065.6794 5518.8855) (3059.542 5520.1069) (3053.4046 5518.8855) (3048.2137 5515.4046)
      (3044.7328 5510.2137)
    ))
    ; P2911 -- see feature_dimensions_mm.csv
    ("06_ORNAMENT" 1 (
      (3043.5115 5427.7405) (3044.7328 5421.6031) (3048.2137 5416.3969) (3053.4046 5412.9313) (3059.542 5411.7099)
      (3065.6794 5412.9313) (3070.8702 5416.3969) (3074.3511 5421.6031) (3075.5725 5427.7405) (3074.3511 5433.8779)
      (3070.8702 5439.0687) (3065.6794 5442.5496) (3059.542 5443.771) (3053.4046 5442.5496) (3048.2137 5439.0687)
      (3044.7328 5433.8779)
    ))
    ; P2912 -- see feature_dimensions_mm.csv
    ("06_ORNAMENT" 1 (
      (3043.5115 5351.4046) (3044.7328 5345.2672) (3048.2137 5340.0611) (3053.4046 5336.5954) (3059.542 5335.374)
      (3065.6794 5336.5954) (3070.8702 5340.0611) (3074.3511 5345.2672) (3075.5725 5351.4046) (3074.3511 5357.542)
      (3070.8702 5362.7328) (3065.6794 5366.2137) (3059.542 5367.4351) (3053.4046 5366.2137) (3048.2137 5362.7328)
      (3044.7328 5357.542)
    ))
    ; P2913 -- see feature_dimensions_mm.csv
    ("06_ORNAMENT" 1 (
      (3043.5115 5275.0687) (3044.7328 5268.9313) (3048.2137 5263.7252) (3053.4046 5260.2595) (3059.542 5259.0382)
      (3065.6794 5260.2595) (3070.8702 5263.7252) (3074.3511 5268.9313) (3075.5725 5275.0687) (3074.3511 5281.2061)
      (3070.8702 5286.3969) (3065.6794 5289.8779) (3059.542 5291.0992) (3053.4046 5289.8779) (3048.2137 5286.3969)
      (3044.7328 5281.2061)
    ))
    ; P2914 -- see feature_dimensions_mm.csv
    ("06_ORNAMENT" 1 (
      (3043.5115 5198.7328) (3044.7328 5192.5954) (3048.2137 5187.3893) (3053.4046 5183.9237) (3059.542 5182.7023)
      (3065.6794 5183.9237) (3070.8702 5187.3893) (3074.3511 5192.5954) (3075.5725 5198.7328) (3074.3511 5204.8702)
      (3070.8702 5210.0611) (3065.6794 5213.542) (3059.542 5214.7634) (3053.4046 5213.542) (3048.2137 5210.0611)
      (3044.7328 5204.8702)
    ))
    ; P2915 -- see feature_dimensions_mm.csv
    ("06_ORNAMENT" 1 (
      (3043.5115 5122.3969) (3044.7328 5116.2595) (3048.2137 5111.0534) (3053.4046 5107.5878) (3059.542 5106.3664)
      (3065.6794 5107.5878) (3070.8702 5111.0534) (3074.3511 5116.2595) (3075.5725 5122.3969) (3074.3511 5128.5344)
      (3070.8702 5133.7252) (3065.6794 5137.2061) (3059.542 5138.4275) (3053.4046 5137.2061) (3048.2137 5133.7252)
      (3044.7328 5128.5344)
    ))
    ; P2916 -- see feature_dimensions_mm.csv
    ("06_ORNAMENT" 1 (
      (3043.5115 5046.0611) (3044.7328 5039.9237) (3048.2137 5034.7176) (3053.4046 5031.2519) (3059.542 5030.0305)
      (3065.6794 5031.2519) (3070.8702 5034.7176) (3074.3511 5039.9237) (3075.5725 5046.0611) (3074.3511 5052.1985)
      (3070.8702 5057.3893) (3065.6794 5060.8702) (3059.542 5062.0916) (3053.4046 5060.8702) (3048.2137 5057.3893)
      (3044.7328 5052.1985)
    ))
    ; P2917 -- see feature_dimensions_mm.csv
    ("06_ORNAMENT" 1 (
      (3043.5115 4969.7252) (3044.7328 4963.5878) (3048.2137 4958.3817) (3053.4046 4954.916) (3059.542 4953.6947)
      (3065.6794 4954.916) (3070.8702 4958.3817) (3074.3511 4963.5878) (3075.5725 4969.7252) (3074.3511 4975.8626)
      (3070.8702 4981.0534) (3065.6794 4984.5344) (3059.542 4985.7557) (3053.4046 4984.5344) (3048.2137 4981.0534)
      (3044.7328 4975.8626)
    ))
    ; P2918 -- see feature_dimensions_mm.csv
    ("06_ORNAMENT" 1 (
      (3043.5115 4893.3893) (3044.7328 4887.2519) (3048.2137 4882.0458) (3053.4046 4878.5802) (3059.542 4877.3588)
      (3065.6794 4878.5802) (3070.8702 4882.0458) (3074.3511 4887.2519) (3075.5725 4893.3893) (3074.3511 4899.5267)
      (3070.8702 4904.7176) (3065.6794 4908.1985) (3059.542 4909.4198) (3053.4046 4908.1985) (3048.2137 4904.7176)
      (3044.7328 4899.5267)
    ))
    ; P2919 -- see feature_dimensions_mm.csv
    ("06_ORNAMENT" 1 (
      (3043.5115 4817.0534) (3044.7328 4810.916) (3048.2137 4805.7099) (3053.4046 4802.2443) (3059.542 4801.0229)
      (3065.6794 4802.2443) (3070.8702 4805.7099) (3074.3511 4810.916) (3075.5725 4817.0534) (3074.3511 4823.1908)
      (3070.8702 4828.3817) (3065.6794 4831.8626) (3059.542 4833.084) (3053.4046 4831.8626) (3048.2137 4828.3817)
      (3044.7328 4823.1908)
    ))
    ; P2920 -- see feature_dimensions_mm.csv
    ("06_ORNAMENT" 1 (
      (3043.5115 4664.3817) (3044.7328 4658.2443) (3048.2137 4653.0382) (3053.4046 4649.5725) (3059.542 4648.3511)
      (3065.6794 4649.5725) (3070.8702 4653.0382) (3074.3511 4658.2443) (3075.5725 4664.3817) (3074.3511 4670.5191)
      (3070.8702 4675.7099) (3065.6794 4679.1908) (3059.542 4680.4122) (3053.4046 4679.1908) (3048.2137 4675.7099)
      (3044.7328 4670.5191)
    ))
    ; P2921 -- see feature_dimensions_mm.csv
    ("06_ORNAMENT" 1 (
      (3043.5115 4588.0458) (3044.7328 4581.9084) (3048.2137 4576.7023) (3053.4046 4573.2366) (3059.542 4572.0153)
      (3065.6794 4573.2366) (3070.8702 4576.7023) (3074.3511 4581.9084) (3075.5725 4588.0458) (3074.3511 4594.1832)
      (3070.8702 4599.374) (3065.6794 4602.855) (3059.542 4604.0763) (3053.4046 4602.855) (3048.2137 4599.374)
      (3044.7328 4594.1832)
    ))
    ; P2922 -- see feature_dimensions_mm.csv
    ("06_ORNAMENT" 1 (
      (3043.5115 4511.7099) (3044.7328 4505.5725) (3048.2137 4500.3664) (3053.4046 4496.9008) (3059.542 4495.6794)
      (3065.6794 4496.9008) (3070.8702 4500.3664) (3074.3511 4505.5725) (3075.5725 4511.7099) (3074.3511 4517.8473)
      (3070.8702 4523.0382) (3065.6794 4526.5191) (3059.542 4527.7405) (3053.4046 4526.5191) (3048.2137 4523.0382)
      (3044.7328 4517.8473)
    ))
    ; P2923 -- see feature_dimensions_mm.csv
    ("06_ORNAMENT" 1 (
      (3043.5115 4359.0382) (3044.7328 4352.9008) (3048.2137 4347.6947) (3053.4046 4344.229) (3059.542 4343.0076)
      (3065.6794 4344.229) (3070.8702 4347.6947) (3074.3511 4352.9008) (3075.5725 4359.0382) (3074.3511 4365.1756)
      (3070.8702 4370.3664) (3065.6794 4373.8473) (3059.542 4375.0687) (3053.4046 4373.8473) (3048.2137 4370.3664)
      (3044.7328 4365.1756)
    ))
    ; P2924 -- see feature_dimensions_mm.csv
    ("06_ORNAMENT" 1 (
      (3043.5115 4282.7023) (3044.7328 4276.5649) (3048.2137 4271.3588) (3053.4046 4267.8931) (3059.542 4266.6718)
      (3065.6794 4267.8931) (3070.8702 4271.3588) (3074.3511 4276.5649) (3075.5725 4282.7023) (3074.3511 4288.8397)
      (3070.8702 4294.0305) (3065.6794 4297.5115) (3059.542 4298.7328) (3053.4046 4297.5115) (3048.2137 4294.0305)
      (3044.7328 4288.8397)
    ))
    ; P2925 -- see feature_dimensions_mm.csv
    ("06_ORNAMENT" 1 (
      (3043.5115 4206.3664) (3044.7328 4200.229) (3048.2137 4195.0229) (3053.4046 4191.5573) (3059.542 4190.3359)
      (3065.6794 4191.5573) (3070.8702 4195.0229) (3074.3511 4200.229) (3075.5725 4206.3664) (3074.3511 4212.5038)
      (3070.8702 4217.6947) (3065.6794 4221.1756) (3059.542 4222.3969) (3053.4046 4221.1756) (3048.2137 4217.6947)
      (3044.7328 4212.5038)
    ))
    ; P2926 -- see feature_dimensions_mm.csv
    ("06_ORNAMENT" 1 (
      (3043.5115 4053.6947) (3044.7328 4047.5573) (3048.2137 4042.3511) (3053.4046 4038.8855) (3059.542 4037.6641)
      (3065.6794 4038.8855) (3070.8702 4042.3511) (3074.3511 4047.5573) (3075.5725 4053.6947) (3074.3511 4059.8321)
      (3070.8702 4065.0229) (3065.6794 4068.5038) (3059.542 4069.7252) (3053.4046 4068.5038) (3048.2137 4065.0229)
      (3044.7328 4059.8321)
    ))
    ; P2927 -- see feature_dimensions_mm.csv
    ("06_ORNAMENT" 1 (
      (3043.5115 3977.3588) (3044.7328 3971.2214) (3048.2137 3966.0153) (3053.4046 3962.5496) (3059.542 3961.3282)
      (3065.6794 3962.5496) (3070.8702 3966.0153) (3074.3511 3971.2214) (3075.5725 3977.3588) (3074.3511 3983.4962)
      (3070.8702 3988.687) (3065.6794 3992.1679) (3059.542 3993.3893) (3053.4046 3992.1679) (3048.2137 3988.687)
      (3044.7328 3983.4962)
    ))
    ; P2928 -- see feature_dimensions_mm.csv
    ("06_ORNAMENT" 1 (
      (3043.5115 3901.0229) (3044.7328 3894.8855) (3048.2137 3889.6794) (3053.4046 3886.2137) (3059.542 3884.9924)
      (3065.6794 3886.2137) (3070.8702 3889.6794) (3074.3511 3894.8855) (3075.5725 3901.0229) (3074.3511 3907.1603)
      (3070.8702 3912.3511) (3065.6794 3915.8321) (3059.542 3917.0534) (3053.4046 3915.8321) (3048.2137 3912.3511)
      (3044.7328 3907.1603)
    ))
    ; P2929 -- see feature_dimensions_mm.csv
    ("06_ORNAMENT" 1 (
      (3056.4885 5938.9313) (3083.0382 5938.9313) (3102.687 5940.3206) (3127.4656 5943.7863) (3152.916 5948.8397)
      (3178.7481 5955.313) (3204.5954 5962.9924) (3230.1679 5971.7099) (3255.145 5981.2672) (3279.1756 5991.4809)
      (3301.9542 6002.1679) (3323.145 6013.1298) (3342.4427 6024.1832) (3359.5267 6035.1298) (3374.0458 6045.8015)
      (3354.1679 6044.9008) (3332.4733 6042.7939) (3309.2824 6039.5573) (3284.9618 6035.1908) (3259.8473 6029.7557)
      (3234.3206 6023.2977) (3208.7023 6015.8321) (3183.3435 6007.4046) (3158.6107 5998.0611) (3134.855 5987.8473)
      (3112.4122 5976.7786) (3091.6336 5964.916) (3072.8702 5952.2901)
    ))
    ; P2930 -- see feature_dimensions_mm.csv
    ("06_ORNAMENT" 1 (
      (3082.9466 5312.9771) (3084.458 5307.313) (3088.6107 5303.1603) (3094.2748 5301.6336) (3099.9389 5303.1603)
      (3104.0916 5307.313) (3105.6183 5312.9771) (3104.0916 5318.6412) (3099.9389 5322.7939) (3094.2748 5324.3053)
      (3088.6107 5322.7939) (3084.458 5318.6412)
    ))
    ; P2931 -- see feature_dimensions_mm.csv
    ("06_ORNAMENT" 1 (
      (3082.9466 4717.5573) (3084.458 4711.8931) (3088.6107 4707.7405) (3094.2748 4706.2137) (3099.9389 4707.7405)
      (3104.0916 4711.8931) (3105.6183 4717.5573) (3104.0916 4723.2214) (3099.9389 4727.374) (3094.2748 4728.8855)
      (3088.6107 4727.374) (3084.458 4723.2214)
    ))
    ; P2932 -- see feature_dimensions_mm.csv
    ("06_ORNAMENT" 1 (
      (3082.9466 4122.1374) (3084.458 4116.4733) (3088.6107 4112.3206) (3094.2748 4110.7939) (3099.9389 4112.3206)
      (3104.0916 4116.4733) (3105.6183 4122.1374) (3104.0916 4127.8015) (3099.9389 4131.9542) (3094.2748 4133.4656)
      (3088.6107 4131.9542) (3084.458 4127.8015)
    ))
    ; P2933 -- see feature_dimensions_mm.csv
    ("06_ORNAMENT" 1 (
      (3103.0687 5414.1985) (3104.5954 5408.5344) (3108.7481 5404.3817) (3114.4122 5402.855) (3120.0763 5404.3817)
      (3124.229 5408.5344) (3125.7405 5414.1985) (3124.229 5419.8626) (3120.0763 5424.0153) (3114.4122 5425.5267)
      (3108.7481 5424.0153) (3104.5954 5419.8626)
    ))
    ; P2934 -- see feature_dimensions_mm.csv
    ("06_ORNAMENT" 1 (
      (3103.0687 5211.7557) (3104.5954 5206.0916) (3108.7481 5201.9389) (3114.4122 5200.4275) (3120.0763 5201.9389)
      (3124.229 5206.0916) (3125.7405 5211.7557) (3124.229 5217.4198) (3120.0763 5221.5725) (3114.4122 5223.0992)
      (3108.7481 5221.5725) (3104.5954 5217.4198)
    ))
    ; P2935 -- see feature_dimensions_mm.csv
    ("06_ORNAMENT" 1 (
      (3103.0687 4818.7786) (3104.5954 4813.1145) (3108.7481 4808.9618) (3114.4122 4807.4351) (3120.0763 4808.9618)
      (3124.229 4813.1145) (3125.7405 4818.7786) (3124.229 4824.4427) (3120.0763 4828.5954) (3114.4122 4830.1069)
      (3108.7481 4828.5954) (3104.5954 4824.4427)
    ))
    ; P2936 -- see feature_dimensions_mm.csv
    ("06_ORNAMENT" 1 (
      (3103.0687 4616.3359) (3104.5954 4610.6718) (3108.7481 4606.5191) (3114.4122 4605.0076) (3120.0763 4606.5191)
      (3124.229 4610.6718) (3125.7405 4616.3359) (3124.229 4622.0) (3120.0763 4626.1527) (3114.4122 4627.6794)
      (3108.7481 4626.1527) (3104.5954 4622.0)
    ))
    ; P2937 -- see feature_dimensions_mm.csv
    ("06_ORNAMENT" 1 (
      (3103.0687 4223.3588) (3104.5954 4217.6947) (3108.7481 4213.542) (3114.4122 4212.0153) (3120.0763 4213.542)
      (3124.229 4217.6947) (3125.7405 4223.3588) (3124.229 4229.0229) (3120.0763 4233.1756) (3114.4122 4234.687)
      (3108.7481 4233.1756) (3104.5954 4229.0229)
    ))
    ; P2938 -- see feature_dimensions_mm.csv
    ("06_ORNAMENT" 1 (
      (3103.0687 4020.916) (3104.5954 4015.2519) (3108.7481 4011.0992) (3114.4122 4009.5878) (3120.0763 4011.0992)
      (3124.229 4015.2519) (3125.7405 4020.916) (3124.229 4026.5802) (3120.0763 4030.7328) (3114.4122 4032.2595)
      (3108.7481 4030.7328) (3104.5954 4026.5802)
    ))
    ; P2939 -- see feature_dimensions_mm.csv
    ("06_ORNAMENT" 1 (
      (3109.3893 4122.1374) (3109.7557 4118.3969) (3110.8702 4114.7481) (3112.3511 4111.9084) (3112.855 4100.626)
      (3115.6641 4079.2672) (3120.3206 4058.2443) (3126.7939 4037.7099) (3135.0382 4017.8015) (3144.9771 3998.7023)
      (3156.5496 3980.5344) (3169.6641 3963.4504) (3177.2977 3955.1298) (3178.2443 3952.0611) (3180.0458 3948.7023)
      (3182.4275 3945.7863) (3185.3435 3943.4046) (3188.7023 3941.6031) (3191.771 3940.6565) (3200.0916 3933.0229)
      (3217.1756 3919.9084) (3235.3435 3908.3359) (3254.4427 3898.3969) (3274.3511 3890.1527) (3294.8855 3883.6794)
      (3315.9084 3879.0229) (3337.2672 3876.2137) (3348.5496 3875.7099) (3351.3893 3874.229) (3355.0382 3873.1145)
      (3358.7786 3872.7481) (3362.5191 3873.1145) (3366.1679 3874.229) (3369.0076 3875.7099) (3380.2901 3876.2137)
      (3401.6489 3879.0229) (3422.6718 3883.6794) (3443.2061 3890.1527) (3463.1145 3898.3969) (3482.2137 3908.3359)
      (3500.3817 3919.9084) (3517.4656 3933.0229) (3525.7863 3940.6565) (3528.855 3941.6031) (3532.2137 3943.4046)
      (3535.1298 3945.7863) (3537.5115 3948.7023) (3539.313 3952.0611) (3540.2595 3955.1298) (3547.8931 3963.4504)
      (3561.0076 3980.5344) (3572.5802 3998.7023) (3582.5191 4017.8015) (3590.7634 4037.7099) (3597.2366 4058.2443)
      (3601.8931 4079.2672) (3604.7023 4100.626) (3605.2061 4111.9084) (3606.687 4114.7481) (3607.8015 4118.3969)
      (3608.1679 4122.1374) (3607.8015 4125.8779) (3606.687 4129.5267) (3605.2061 4132.3664) (3604.7023 4143.6489)
      (3601.8931 4165.0076) (3597.2366 4186.0305) (3590.7634 4206.5649) (3582.5191 4226.4733) (3572.5802 4245.5725)
      (3561.0076 4263.7405) (3547.8931 4280.8244) (3540.2595 4289.145) (3539.313 4292.2137) (3537.5115 4295.5725)
      (3535.1298 4298.4885) (3532.2137 4300.8702) (3528.855 4302.6718) (3525.7863 4303.6183) (3517.4656 4311.2519)
      (3500.3817 4324.3664) (3482.2137 4335.9389) (3463.1145 4345.8779) (3443.2061 4354.1221) (3422.6718 4360.5954)
      (3401.6489 4365.2519) (3380.2901 4368.0611) (3369.0076 4368.5649) (3366.1679 4370.0458) (3362.5191 4371.1603)
      (3358.7786 4371.5267) (3355.0382 4371.1603) (3351.3893 4370.0458) (3348.5496 4368.5649) (3337.2672 4368.0611)
      (3315.9084 4365.2519) (3294.8855 4360.5954) (3274.3511 4354.1221) (3254.4427 4345.8779) (3235.3435 4335.9389)
      (3217.1756 4324.3664) (3200.0916 4311.2519) (3191.771 4303.6183) (3188.7023 4302.6718) (3185.3435 4300.8702)
      (3182.4275 4298.4885) (3180.0458 4295.5725) (3178.2443 4292.2137) (3177.2977 4289.145) (3169.6641 4280.8244)
      (3156.5496 4263.7405) (3144.9771 4245.5725) (3135.0382 4226.4733) (3126.7939 4206.5649) (3120.3206 4186.0305)
      (3115.6641 4165.0076) (3112.855 4143.6489) (3112.3511 4132.3664) (3110.8702 4129.5267) (3109.7557 4125.8779)
    ))
    ; P2940 -- see feature_dimensions_mm.csv
    ("06_ORNAMENT" 1 (
      (3138.0916 5393.9542) (3139.3282 5386.1679) (3142.9008 5379.145) (3148.4733 5373.5725) (3155.4962 5370.0)
      (3163.2824 5368.7634) (3171.0687 5370.0) (3178.0916 5373.5725) (3183.6641 5379.145) (3187.2366 5386.1679)
      (3188.4733 5393.9542) (3187.2366 5401.7405) (3183.6641 5408.7634) (3178.0916 5414.3359) (3171.0687 5417.9084)
      (3163.2824 5419.145) (3155.4962 5417.9084) (3148.4733 5414.3359) (3142.9008 5408.7634) (3139.3282 5401.7405)
    ))
    ; P2941 -- see feature_dimensions_mm.csv
    ("06_ORNAMENT" 1 (
      (3138.0916 5232.0) (3139.3282 5224.2137) (3142.9008 5217.1908) (3148.4733 5211.6183) (3155.4962 5208.0458)
      (3163.2824 5206.8092) (3171.0687 5208.0458) (3178.0916 5211.6183) (3183.6641 5217.1908) (3187.2366 5224.2137)
      (3188.4733 5232.0) (3187.2366 5239.7863) (3183.6641 5246.8092) (3178.0916 5252.3817) (3171.0687 5255.9542)
      (3163.2824 5257.1908) (3155.4962 5255.9542) (3148.4733 5252.3817) (3142.9008 5246.8092) (3139.3282 5239.7863)
    ))
    ; P2942 -- see feature_dimensions_mm.csv
    ("06_ORNAMENT" 1 (
      (3138.0916 4798.5344) (3139.3282 4790.7481) (3142.9008 4783.7252) (3148.4733 4778.1527) (3155.4962 4774.5802)
      (3163.2824 4773.3435) (3171.0687 4774.5802) (3178.0916 4778.1527) (3183.6641 4783.7252) (3187.2366 4790.7481)
      (3188.4733 4798.5344) (3187.2366 4806.3206) (3183.6641 4813.3435) (3178.0916 4818.916) (3171.0687 4822.4885)
      (3163.2824 4823.7252) (3155.4962 4822.4885) (3148.4733 4818.916) (3142.9008 4813.3435) (3139.3282 4806.3206)
    ))
    ; P2943 -- see feature_dimensions_mm.csv
    ("06_ORNAMENT" 1 (
      (3138.0916 4636.5802) (3139.3282 4628.7939) (3142.9008 4621.771) (3148.4733 4616.1985) (3155.4962 4612.626)
      (3163.2824 4611.3893) (3171.0687 4612.626) (3178.0916 4616.1985) (3183.6641 4621.771) (3187.2366 4628.7939)
      (3188.4733 4636.5802) (3187.2366 4644.3664) (3183.6641 4651.3893) (3178.0916 4656.9618) (3171.0687 4660.5344)
      (3163.2824 4661.771) (3155.4962 4660.5344) (3148.4733 4656.9618) (3142.9008 4651.3893) (3139.3282 4644.3664)
    ))
    ; P2944 -- see feature_dimensions_mm.csv
    ("06_ORNAMENT" 1 (
      (3138.0916 4203.1145) (3139.3282 4195.3282) (3142.9008 4188.3053) (3148.4733 4182.7328) (3155.4962 4179.1603)
      (3163.2824 4177.9237) (3171.0687 4179.1603) (3178.0916 4182.7328) (3183.6641 4188.3053) (3187.2366 4195.3282)
      (3188.4733 4203.1145) (3187.2366 4210.9008) (3183.6641 4217.9237) (3178.0916 4223.4962) (3171.0687 4227.0687)
      (3163.2824 4228.3053) (3155.4962 4227.0687) (3148.4733 4223.4962) (3142.9008 4217.9237) (3139.3282 4210.9008)
    ))
    ; P2945 -- see feature_dimensions_mm.csv
    ("06_ORNAMENT" 1 (
      (3138.0916 4041.1603) (3139.3282 4033.374) (3142.9008 4026.3511) (3148.4733 4020.7786) (3155.4962 4017.2061)
      (3163.2824 4015.9695) (3171.0687 4017.2061) (3178.0916 4020.7786) (3183.6641 4026.3511) (3187.2366 4033.374)
      (3188.4733 4041.1603) (3187.2366 4048.9466) (3183.6641 4055.9695) (3178.0916 4061.542) (3171.0687 4065.1145)
      (3163.2824 4066.3511) (3155.4962 4065.1145) (3148.4733 4061.542) (3142.9008 4055.9695) (3139.3282 4048.9466)
    ))
    ; P2946 -- see feature_dimensions_mm.csv
    ("06_ORNAMENT" 1 (
      (3160.4122 5500.0153) (3161.9237 5494.3359) (3166.0763 5490.1985) (3171.7405 5488.6718) (3177.4198 5490.1985)
      (3181.5573 5494.3359) (3183.084 5500.0153) (3181.5573 5505.6794) (3177.4198 5509.8321) (3171.7405 5511.3435)
      (3166.0763 5509.8321) (3161.9237 5505.6794)
    ))
    ; P2947 -- see feature_dimensions_mm.csv
    ("06_ORNAMENT" 1 (
      (3160.4122 5125.9389) (3161.9237 5120.2748) (3166.0763 5116.1221) (3171.7405 5114.6107) (3177.4198 5116.1221)
      (3181.5573 5120.2748) (3183.084 5125.9389) (3181.5573 5131.6183) (3177.4198 5135.7557) (3171.7405 5137.2824)
      (3166.0763 5135.7557) (3161.9237 5131.6183)
    ))
    ; P2948 -- see feature_dimensions_mm.csv
    ("06_ORNAMENT" 1 (
      (3160.4122 4904.5954) (3161.9237 4898.916) (3166.0763 4894.7786) (3171.7405 4893.2519) (3177.4198 4894.7786)
      (3181.5573 4898.916) (3183.084 4904.5954) (3181.5573 4910.2595) (3177.4198 4914.4122) (3171.7405 4915.9237)
      (3166.0763 4914.4122) (3161.9237 4910.2595)
    ))
    ; P2949 -- see feature_dimensions_mm.csv
    ("06_ORNAMENT" 1 (
      (3160.4122 4530.5191) (3161.9237 4524.855) (3166.0763 4520.7023) (3171.7405 4519.1908) (3177.4198 4520.7023)
      (3181.5573 4524.855) (3183.084 4530.5191) (3181.5573 4536.1985) (3177.4198 4540.3359) (3171.7405 4541.8626)
      (3166.0763 4540.3359) (3161.9237 4536.1985)
    ))
    ; P2950 -- see feature_dimensions_mm.csv
    ("06_ORNAMENT" 1 (
      (3160.4122 4309.1756) (3161.9237 4303.4962) (3166.0763 4299.3588) (3171.7405 4297.8321) (3177.4198 4299.3588)
      (3181.5573 4303.4962) (3183.084 4309.1756) (3181.5573 4314.8397) (3177.4198 4318.9924) (3171.7405 4320.5038)
      (3166.0763 4318.9924) (3161.9237 4314.8397)
    ))
    ; P2951 -- see feature_dimensions_mm.csv
    ("06_ORNAMENT" 1 (
      (3160.4122 3935.0992) (3161.9237 3929.4351) (3166.0763 3925.2824) (3171.7405 3923.771) (3177.4198 3925.2824)
      (3181.5573 3929.4351) (3183.084 3935.0992) (3181.5573 3940.7786) (3177.4198 3944.916) (3171.7405 3946.4427)
      (3166.0763 3944.916) (3161.9237 3940.7786)
    ))
    ; P2952 -- see feature_dimensions_mm.csv
    ("06_ORNAMENT" 1 (
      (3169.8473 5312.9771) (3170.5649 5307.8473) (3172.687 5302.855) (3176.1679 5298.1069) (3180.916 5293.7252)
      (3186.8244 5289.8168) (3193.7252 5286.4885) (3201.4809 5283.8015) (3209.8779 5281.8321) (3218.7176 5280.626)
      (3227.7863 5280.229) (3236.855 5280.626) (3245.6947 5281.8321) (3254.0916 5283.8015) (3261.8473 5286.4885)
      (3268.7481 5289.8168) (3274.6565 5293.7252) (3279.4046 5298.1069) (3282.8855 5302.855) (3285.0076 5307.8473)
      (3285.7252 5312.9771) (3285.0076 5318.1069) (3282.8855 5323.0992) (3279.4046 5327.8473) (3274.6565 5332.229)
      (3268.7481 5336.1374) (3261.8473 5339.4656) (3254.0916 5342.1527) (3245.6947 5344.1221) (3236.855 5345.3282)
      (3227.7863 5345.7252) (3218.7176 5345.3282) (3209.8779 5344.1221) (3201.4809 5342.1527) (3193.7252 5339.4656)
      (3186.8244 5336.1374) (3180.916 5332.229) (3176.1679 5327.8473) (3172.687 5323.0992) (3170.5649 5318.1069)
    ))
    ; P2953 -- see feature_dimensions_mm.csv
    ("06_ORNAMENT" 1 (
      (3169.8473 4717.5573) (3170.5649 4712.4275) (3172.687 4707.4351) (3176.1679 4702.687) (3180.916 4698.3053)
      (3186.8244 4694.3969) (3193.7252 4691.0687) (3201.4809 4688.3817) (3209.8779 4686.4122) (3218.7176 4685.2061)
      (3227.7863 4684.8092) (3236.855 4685.2061) (3245.6947 4686.4122) (3254.0916 4688.3817) (3261.8473 4691.0687)
      (3268.7481 4694.3969) (3274.6565 4698.3053) (3279.4046 4702.687) (3282.8855 4707.4351) (3285.0076 4712.4275)
      (3285.7252 4717.5573) (3285.0076 4722.687) (3282.8855 4727.6794) (3279.4046 4732.4275) (3274.6565 4736.8092)
      (3268.7481 4740.7176) (3261.8473 4744.0458) (3254.0916 4746.7328) (3245.6947 4748.7023) (3236.855 4749.9084)
      (3227.7863 4750.3053) (3218.7176 4749.9084) (3209.8779 4748.7023) (3201.4809 4746.7328) (3193.7252 4744.0458)
      (3186.8244 4740.7176) (3180.916 4736.8092) (3176.1679 4732.4275) (3172.687 4727.6794) (3170.5649 4722.687)
    ))
    ; P2954 -- see feature_dimensions_mm.csv
    ("06_ORNAMENT" 1 (
      (3169.8473 4122.1374) (3170.5649 4117.0076) (3172.687 4112.0153) (3176.1679 4107.2672) (3180.916 4102.8855)
      (3186.8244 4098.9771) (3193.7252 4095.6489) (3201.4809 4092.9618) (3209.8779 4090.9924) (3218.7176 4089.7863)
      (3227.7863 4089.3893) (3236.855 4089.7863) (3245.6947 4090.9924) (3254.0916 4092.9618) (3261.8473 4095.6489)
      (3268.7481 4098.9771) (3274.6565 4102.8855) (3279.4046 4107.2672) (3282.8855 4112.0153) (3285.0076 4117.0076)
      (3285.7252 4122.1374) (3285.0076 4127.2672) (3282.8855 4132.2595) (3279.4046 4137.0076) (3274.6565 4141.3893)
      (3268.7481 4145.2977) (3261.8473 4148.626) (3254.0916 4151.313) (3245.6947 4153.2824) (3236.855 4154.4885)
      (3227.7863 4154.8855) (3218.7176 4154.4885) (3209.8779 4153.2824) (3201.4809 4151.313) (3193.7252 4148.626)
      (3186.8244 4145.2977) (3180.916 4141.3893) (3176.1679 4137.0076) (3172.687 4132.2595) (3170.5649 4127.2672)
    ))
    ; P2955 -- see feature_dimensions_mm.csv
    ("06_ORNAMENT" 1 (
      (3181.6794 7374.0458) (3183.0382 7371.5267) (3186.7481 7369.4809) (3191.7863 7368.1527) (3196.8397 7367.4656)
      (3200.626 7367.0076) (3202.3053 7366.1527) (3201.7099 7364.3511) (3199.374 7361.3435) (3196.2901 7357.2824)
      (3193.6641 7352.7786) (3192.4885 7348.7176) (3193.313 7345.9847) (3196.0458 7345.1603) (3200.1069 7346.3359)
      (3204.6107 7348.9618) (3208.6718 7352.0458) (3211.6794 7354.3817) (3213.4809 7354.9771) (3214.3359 7353.2977)
      (3214.7939 7349.5115) (3215.4962 7344.458) (3216.8092 7339.4198) (3218.855 7335.7099) (3221.374 7334.3511)
      (3223.8931 7335.7099) (3225.9389 7339.4198) (3227.2672 7344.458) (3227.9542 7349.5115) (3228.4122 7353.2977)
      (3229.2672 7354.9771) (3231.0687 7354.3817) (3234.0763 7352.0458) (3238.1374 7348.9618) (3242.6412 7346.3359)
      (3246.7023 7345.1603) (3249.4351 7345.9847) (3250.2595 7348.7176) (3249.084 7352.7786) (3246.458 7357.2824)
      (3243.374 7361.3435) (3241.0382 7364.3511) (3240.4427 7366.1527) (3242.1221 7367.0076) (3245.9084 7367.4656)
      (3250.9618 7368.1527) (3256.0 7369.4809) (3259.7099 7371.5267) (3261.0687 7374.0458) (3259.7099 7376.5649)
      (3256.0 7378.6107) (3250.9618 7379.9237) (3245.9084 7380.626) (3242.1221 7381.084) (3240.4427 7381.9389)
      (3241.0382 7383.7405) (3243.374 7386.7481) (3246.458 7390.8092) (3249.084 7395.313) (3250.2595 7399.374)
      (3249.4351 7402.1069) (3246.7023 7402.9313) (3242.6412 7401.7557) (3238.1374 7399.1298) (3234.0763 7396.0458)
      (3231.0687 7393.7099) (3229.2672 7393.1145) (3228.4122 7394.7939) (3227.9542 7398.5802) (3227.2672 7403.6336)
      (3225.9389 7408.6718) (3223.8931 7412.3817) (3221.374 7413.7405) (3218.855 7412.3817) (3216.8092 7408.6718)
      (3215.4962 7403.6336) (3214.7939 7398.5802) (3214.3359 7394.7939) (3213.4809 7393.1145) (3211.6794 7393.7099)
      (3208.6718 7396.0458) (3204.6107 7399.1298) (3200.1069 7401.7557) (3196.0458 7402.9313) (3193.313 7402.1069)
      (3192.4885 7399.374) (3193.6641 7395.313) (3196.2901 7390.8092) (3199.374 7386.7481) (3201.7099 7383.7405)
      (3202.3053 7381.9389) (3200.626 7381.084) (3196.8397 7380.626) (3191.7863 7379.9237) (3186.7481 7378.6107)
      (3183.0382 7376.5649)
    ))
    ; P2956 -- see feature_dimensions_mm.csv
    ("06_ORNAMENT" 1 (
      (3181.6794 7206.1069) (3183.0382 7203.5878) (3186.7481 7201.542) (3191.7863 7200.2137) (3196.8397 7199.5267)
      (3200.626 7199.0687) (3202.3053 7198.2137) (3201.7099 7196.4122) (3199.374 7193.4046) (3196.2901 7189.3435)
      (3193.6641 7184.8397) (3192.4885 7180.7786) (3193.313 7178.0458) (3196.0458 7177.2214) (3200.1069 7178.3969)
      (3204.6107 7181.0229) (3208.6718 7184.1069) (3211.6794 7186.4427) (3213.4809 7187.0382) (3214.3359 7185.3588)
      (3214.7939 7181.5725) (3215.4962 7176.5191) (3216.8092 7171.4809) (3218.855 7167.771) (3221.374 7166.4122)
      (3223.8931 7167.771) (3225.9389 7171.4809) (3227.2672 7176.5191) (3227.9542 7181.5725) (3228.4122 7185.3588)
      (3229.2672 7187.0382) (3231.0687 7186.4427) (3234.0763 7184.1069) (3238.1374 7181.0229) (3242.6412 7178.3969)
      (3246.7023 7177.2214) (3249.4351 7178.0458) (3250.2595 7180.7786) (3249.084 7184.8397) (3246.458 7189.3435)
      (3243.374 7193.4046) (3241.0382 7196.4122) (3240.4427 7198.2137) (3242.1221 7199.0687) (3245.9084 7199.5267)
      (3250.9618 7200.2137) (3256.0 7201.542) (3259.7099 7203.5878) (3261.0687 7206.1069) (3259.7099 7208.626)
      (3256.0 7210.6718) (3250.9618 7211.9847) (3245.9084 7212.687) (3242.1221 7213.145) (3240.4427 7214.0)
      (3241.0382 7215.8015) (3243.374 7218.8092) (3246.458 7222.8702) (3249.084 7227.374) (3250.2595 7231.4351)
      (3249.4351 7234.1679) (3246.7023 7234.9924) (3242.6412 7233.8168) (3238.1374 7231.1908) (3234.0763 7228.1069)
      (3231.0687 7225.771) (3229.2672 7225.1756) (3228.4122 7226.855) (3227.9542 7230.6412) (3227.2672 7235.6947)
      (3225.9389 7240.7328) (3223.8931 7244.4427) (3221.374 7245.8015) (3218.855 7244.4427) (3216.8092 7240.7328)
      (3215.4962 7235.6947) (3214.7939 7230.6412) (3214.3359 7226.855) (3213.4809 7225.1756) (3211.6794 7225.771)
      (3208.6718 7228.1069) (3204.6107 7231.1908) (3200.1069 7233.8168) (3196.0458 7234.9924) (3193.313 7234.1679)
      (3192.4885 7231.4351) (3193.6641 7227.374) (3196.2901 7222.8702) (3199.374 7218.8092) (3201.7099 7215.8015)
      (3202.3053 7214.0) (3200.626 7213.145) (3196.8397 7212.687) (3191.7863 7211.9847) (3186.7481 7210.6718)
      (3183.0382 7208.626)
    ))
    ; P2957 -- see feature_dimensions_mm.csv
    ("06_ORNAMENT" 1 (
      (3181.6794 5022.9008) (3182.0916 5020.3206) (3183.2824 5017.8931) (3185.1756 5015.6947) (3187.6336 5013.8626)
      (3190.4733 5012.4122) (3193.4962 5011.3588) (3196.5344 5010.6412) (3199.374 5010.1985) (3201.8931 5009.8779)
      (3203.9847 5009.5573) (3205.6183 5009.084) (3206.7786 5008.3053) (3207.5573 5007.145) (3208.0305 5005.5115)
      (3208.3511 5003.4198) (3208.6718 5000.9008) (3209.1145 4998.0611) (3209.8321 4995.0229) (3210.8855 4992.0)
      (3212.3359 4989.1603) (3214.1679 4986.7023) (3216.3664 4984.8092) (3218.7939 4983.6183) (3221.374 4983.2061)
      (3223.9542 4983.6183) (3226.3817 4984.8092) (3228.5802 4986.7023) (3230.4122 4989.1603) (3231.8626 4992.0)
      (3232.916 4995.0229) (3233.6336 4998.0611) (3234.0763 5000.9008) (3234.3969 5003.4198) (3234.7176 5005.5115)
      (3235.1908 5007.145) (3235.9695 5008.3053) (3237.1298 5009.084) (3238.7634 5009.5573) (3240.855 5009.8779)
      (3243.374 5010.1985) (3246.2137 5010.6412) (3249.2519 5011.3588) (3252.2748 5012.4122) (3255.1145 5013.8626)
      (3257.5725 5015.6947) (3259.4656 5017.8931) (3260.6565 5020.3206) (3261.0687 5022.9008) (3260.6565 5025.4809)
      (3259.4656 5027.9084) (3257.5725 5030.1069) (3255.1145 5031.9389) (3252.2748 5033.3893) (3249.2519 5034.4427)
      (3246.2137 5035.1603) (3243.374 5035.6031) (3240.855 5035.9237) (3238.7634 5036.2443) (3237.1298 5036.7176)
      (3235.9695 5037.4962) (3235.1908 5038.6565) (3234.7176 5040.2901) (3234.3969 5042.3817) (3234.0763 5044.9008)
      (3233.6336 5047.7405) (3232.916 5050.7786) (3231.8626 5053.8015) (3230.4122 5056.6412) (3228.5802 5059.0992)
      (3226.3817 5060.9924) (3223.9542 5062.1832) (3221.374 5062.5954) (3218.7939 5062.1832) (3216.3664 5060.9924)
      (3214.1679 5059.0992) (3212.3359 5056.6412) (3210.8855 5053.8015) (3209.8321 5050.7786) (3209.1145 5047.7405)
      (3208.6718 5044.9008) (3208.3511 5042.3817) (3208.0305 5040.2901) (3207.5573 5038.6565) (3206.7786 5037.4962)
      (3205.6183 5036.7176) (3203.9847 5036.2443) (3201.8931 5035.9237) (3199.374 5035.6031) (3196.5344 5035.1603)
      (3193.4962 5034.4427) (3190.4733 5033.3893) (3187.6336 5031.9389) (3185.1756 5030.1069) (3183.2824 5027.9084)
      (3182.0916 5025.4809)
    ))
    ; P2958 -- see feature_dimensions_mm.csv
    ("06_ORNAMENT" 1 (
      (3212.2443 7374.0458) (3212.9466 7370.5496) (3214.916 7367.5878) (3217.8779 7365.6183) (3221.374 7364.916)
      (3224.8702 7365.6183) (3227.8321 7367.5878) (3229.8015 7370.5496) (3230.5038 7374.0458) (3229.8015 7377.542)
      (3227.8321 7380.5038) (3224.8702 7382.4733) (3221.374 7383.1756) (3217.8779 7382.4733) (3214.916 7380.5038)
      (3212.9466 7377.542)
    ))
    ; P2959 -- see feature_dimensions_mm.csv
    ("06_ORNAMENT" 1 (
      (3212.2443 7206.1069) (3212.9466 7202.6107) (3214.916 7199.6489) (3217.8779 7197.6794) (3221.374 7196.9771)
      (3224.8702 7197.6794) (3227.8321 7199.6489) (3229.8015 7202.6107) (3230.5038 7206.1069) (3229.8015 7209.6031)
      (3227.8321 7212.5649) (3224.8702 7214.5344) (3221.374 7215.2366) (3217.8779 7214.5344) (3214.916 7212.5649)
      (3212.9466 7209.6031)
    ))
    ; P2960 -- see feature_dimensions_mm.csv
    ("06_ORNAMENT" 1 (
      (3219.1298 5431.5878) (3219.4046 5425.1298) (3220.8092 5418.1985) (3223.3435 5410.9466) (3226.916 5403.5725)
      (3231.4656 5396.2443) (3236.8702 5389.145) (3242.9924 5382.4427) (3249.6947 5376.3206) (3256.7939 5370.916)
      (3264.1221 5366.3664) (3271.4962 5362.7939) (3278.7481 5360.2595) (3285.6794 5358.8397) (3292.1374 5358.5802)
      (3297.9542 5359.4809) (3302.9924 5361.5115) (3307.1145 5364.6412) (3310.2443 5368.7634) (3312.2748 5373.8015)
      (3313.1756 5379.6183) (3312.916 5386.0763) (3311.4962 5393.0076) (3308.9618 5400.2595) (3305.3893 5407.6336)
      (3300.8397 5414.9618) (3295.4351 5422.0611) (3289.313 5428.7634) (3282.6107 5434.8855) (3275.5115 5440.2901)
      (3268.1832 5444.8397) (3260.8092 5448.4122) (3253.5573 5450.9466) (3246.626 5452.3511) (3240.1679 5452.626)
      (3234.3511 5451.7252) (3229.313 5449.6947) (3225.1908 5446.5649) (3222.0611 5442.4427) (3220.0305 5437.4046)
    ))
    ; P2961 -- see feature_dimensions_mm.csv
    ("06_ORNAMENT" 1 (
      (3219.1298 5194.3664) (3220.0305 5188.5496) (3222.0611 5183.5115) (3225.1908 5179.3893) (3229.313 5176.2595)
      (3234.3511 5174.229) (3240.1679 5173.3282) (3246.626 5173.6031) (3253.5573 5175.0076) (3260.8092 5177.542)
      (3268.1832 5181.1145) (3275.5115 5185.6641) (3282.6107 5191.0687) (3289.313 5197.1908) (3295.4351 5203.8931)
      (3300.8397 5210.9924) (3305.3893 5218.3206) (3308.9618 5225.6947) (3311.4962 5232.9466) (3312.916 5239.8779)
      (3313.1756 5246.3359) (3312.2748 5252.1527) (3310.2443 5257.1908) (3307.1145 5261.313) (3302.9924 5264.4427)
      (3297.9542 5266.4733) (3292.1374 5267.374) (3285.6794 5267.1145) (3278.7481 5265.6947) (3271.4962 5263.1603)
      (3264.1221 5259.5878) (3256.7939 5255.0382) (3249.6947 5249.6336) (3242.9924 5243.5115) (3236.8702 5236.8092)
      (3231.4656 5229.7099) (3226.916 5222.3817) (3223.3435 5215.0076) (3220.8092 5207.7557) (3219.4046 5200.8244)
    ))
    ; P2962 -- see feature_dimensions_mm.csv
    ("06_ORNAMENT" 1 (
      (3219.1298 4836.1679) (3219.4046 4829.7099) (3220.8092 4822.7786) (3223.3435 4815.5267) (3226.916 4808.1527)
      (3231.4656 4800.8244) (3236.8702 4793.7252) (3242.9924 4787.0229) (3249.6947 4780.9008) (3256.7939 4775.4962)
      (3264.1221 4770.9466) (3271.4962 4767.374) (3278.7481 4764.8397) (3285.6794 4763.4198) (3292.1374 4763.1603)
      (3297.9542 4764.0611) (3302.9924 4766.0916) (3307.1145 4769.2214) (3310.2443 4773.3435) (3312.2748 4778.3817)
      (3313.1756 4784.1985) (3312.916 4790.6565) (3311.4962 4797.5878) (3308.9618 4804.8397) (3305.3893 4812.2137)
      (3300.8397 4819.542) (3295.4351 4826.6412) (3289.313 4833.3435) (3282.6107 4839.4656) (3275.5115 4844.8702)
      (3268.1832 4849.4198) (3260.8092 4852.9924) (3253.5573 4855.5267) (3246.626 4856.9313) (3240.1679 4857.2061)
      (3234.3511 4856.3053) (3229.313 4854.2748) (3225.1908 4851.145) (3222.0611 4847.0229) (3220.0305 4841.9847)
    ))
    ; P2963 -- see feature_dimensions_mm.csv
    ("06_ORNAMENT" 1 (
      (3219.1298 4598.9466) (3220.0305 4593.1298) (3222.0611 4588.0916) (3225.1908 4583.9695) (3229.313 4580.8397)
      (3234.3511 4578.8092) (3240.1679 4577.9084) (3246.626 4578.1832) (3253.5573 4579.5878) (3260.8092 4582.1221)
      (3268.1832 4585.6947) (3275.5115 4590.2443) (3282.6107 4595.6489) (3289.313 4601.771) (3295.4351 4608.4733)
      (3300.8397 4615.5725) (3305.3893 4622.9008) (3308.9618 4630.2748) (3311.4962 4637.5267) (3312.916 4644.458)
      (3313.1756 4650.916) (3312.2748 4656.7328) (3310.2443 4661.771) (3307.1145 4665.8931) (3302.9924 4669.0229)
      (3297.9542 4671.0534) (3292.1374 4671.9542) (3285.6794 4671.6947) (3278.7481 4670.2748) (3271.4962 4667.7405)
      (3264.1221 4664.1679) (3256.7939 4659.6183) (3249.6947 4654.2137) (3242.9924 4648.0916) (3236.8702 4641.3893)
      (3231.4656 4634.2901) (3226.916 4626.9618) (3223.3435 4619.5878) (3220.8092 4612.3359) (3219.4046 4605.4046)
    ))
    ; P2964 -- see feature_dimensions_mm.csv
    ("06_ORNAMENT" 1 (
      (3219.1298 4240.7481) (3219.4046 4234.2901) (3220.8092 4227.3588) (3223.3435 4220.1069) (3226.916 4212.7328)
      (3231.4656 4205.4046) (3236.8702 4198.3053) (3242.9924 4191.6031) (3249.6947 4185.4809) (3256.7939 4180.0763)
      (3264.1221 4175.5267) (3271.4962 4171.9542) (3278.7481 4169.4198) (3285.6794 4168.0) (3292.1374 4167.7405)
      (3297.9542 4168.6412) (3302.9924 4170.6718) (3307.1145 4173.8015) (3310.2443 4177.9237) (3312.2748 4182.9618)
      (3313.1756 4188.7786) (3312.916 4195.2366) (3311.4962 4202.1679) (3308.9618 4209.4198) (3305.3893 4216.7939)
      (3300.8397 4224.1221) (3295.4351 4231.2214) (3289.313 4237.9237) (3282.6107 4244.0458) (3275.5115 4249.4504)
      (3268.1832 4254.0) (3260.8092 4257.5725) (3253.5573 4260.1069) (3246.626 4261.5115) (3240.1679 4261.7863)
      (3234.3511 4260.8855) (3229.313 4258.855) (3225.1908 4255.7252) (3222.0611 4251.6031) (3220.0305 4246.5649)
    ))
    ; P2965 -- see feature_dimensions_mm.csv
    ("06_ORNAMENT" 1 (
      (3219.1298 4003.5267) (3220.0305 3997.7099) (3222.0611 3992.6718) (3225.1908 3988.5496) (3229.313 3985.4198)
      (3234.3511 3983.3893) (3240.1679 3982.4885) (3246.626 3982.7634) (3253.5573 3984.1679) (3260.8092 3986.7023)
      (3268.1832 3990.2748) (3275.5115 3994.8244) (3282.6107 4000.229) (3289.313 4006.3511) (3295.4351 4013.0534)
      (3300.8397 4020.1527) (3305.3893 4027.4809) (3308.9618 4034.855) (3311.4962 4042.1069) (3312.916 4049.0382)
      (3313.1756 4055.4962) (3312.2748 4061.313) (3310.2443 4066.3511) (3307.1145 4070.4733) (3302.9924 4073.6031)
      (3297.9542 4075.6336) (3292.1374 4076.5344) (3285.6794 4076.2748) (3278.7481 4074.855) (3271.4962 4072.3206)
      (3264.1221 4068.7481) (3256.7939 4064.1985) (3249.6947 4058.7939) (3242.9924 4052.6718) (3236.8702 4045.9695)
      (3231.4656 4038.8702) (3226.916 4031.542) (3223.3435 4024.1679) (3220.8092 4016.916) (3219.4046 4009.9847)
    ))
    ; P2966 -- see feature_dimensions_mm.csv
    ("06_ORNAMENT" 1 (
      (3246.229 5068.6107) (3247.7405 5062.9466) (3251.8931 5058.7939) (3257.5573 5057.2672) (3263.2214 5058.7939)
      (3267.374 5062.9466) (3268.9008 5068.6107) (3267.374 5074.2748) (3263.2214 5078.4275) (3257.5573 5079.9389)
      (3251.8931 5078.4275) (3247.7405 5074.2748)
    ))
    ; P2967 -- see feature_dimensions_mm.csv
    ("06_ORNAMENT" 1 (
      (3246.229 4961.9237) (3247.7405 4956.2595) (3251.8931 4952.1069) (3257.5573 4950.5954) (3263.2214 4952.1069)
      (3267.374 4956.2595) (3268.9008 4961.9237) (3267.374 4967.5878) (3263.2214 4971.7405) (3257.5573 4973.2672)
      (3251.8931 4971.7405) (3247.7405 4967.5878)
    ))
    ; P2968 -- see feature_dimensions_mm.csv
    ("06_ORNAMENT" 1 (
      (3246.229 4366.5038) (3247.7405 4360.8397) (3251.8931 4356.687) (3257.5573 4355.1756) (3263.2214 4356.687)
      (3267.374 4360.8397) (3268.9008 4366.5038) (3267.374 4372.1679) (3263.2214 4376.3206) (3257.5573 4377.8473)
      (3251.8931 4376.3206) (3247.7405 4372.1679)
    ))
    ; P2969 -- see feature_dimensions_mm.csv
    ("06_ORNAMENT" 1 (
      (3246.229 3877.771) (3247.7405 3872.1069) (3251.8931 3867.9542) (3257.5573 3866.4275) (3263.2214 3867.9542)
      (3267.374 3872.1069) (3268.9008 3877.771) (3267.374 3883.4351) (3263.2214 3887.5878) (3257.5573 3889.0992)
      (3251.8931 3887.5878) (3247.7405 3883.4351)
    ))
    ; P2970 -- see feature_dimensions_mm.csv
    ("06_ORNAMENT" 1 (
      (3252.6107 5117.4809) (3253.8473 5109.6947) (3257.4198 5102.6718) (3262.9924 5097.0992) (3270.0153 5093.5267)
      (3277.8015 5092.2901) (3285.5878 5093.5267) (3292.6107 5097.0992) (3298.1832 5102.6718) (3301.7557 5109.6947)
      (3302.9924 5117.4809) (3301.7557 5125.2672) (3298.1832 5132.2901) (3292.6107 5137.8626) (3285.5878 5141.4351)
      (3277.8015 5142.6718) (3270.0153 5141.4351) (3262.9924 5137.8626) (3257.4198 5132.2901) (3253.8473 5125.2672)
    ))
    ; P2971 -- see feature_dimensions_mm.csv
    ("06_ORNAMENT" 1 (
      (3252.6107 4913.0534) (3253.8473 4905.2672) (3257.4198 4898.2443) (3262.9924 4892.6718) (3270.0153 4889.0992)
      (3277.8015 4887.8626) (3285.5878 4889.0992) (3292.6107 4892.6718) (3298.1832 4898.2443) (3301.7557 4905.2672)
      (3302.9924 4913.0534) (3301.7557 4920.8397) (3298.1832 4927.8626) (3292.6107 4933.4351) (3285.5878 4937.0076)
      (3277.8015 4938.2443) (3270.0153 4937.0076) (3262.9924 4933.4351) (3257.4198 4927.8626) (3253.8473 4920.8397)
    ))
    ; P2972 -- see feature_dimensions_mm.csv
    ("06_ORNAMENT" 1 (
      (3252.6107 4522.0611) (3253.8473 4514.2748) (3257.4198 4507.2519) (3262.9924 4501.6794) (3270.0153 4498.1069)
      (3277.8015 4496.8702) (3285.5878 4498.1069) (3292.6107 4501.6794) (3298.1832 4507.2519) (3301.7557 4514.2748)
      (3302.9924 4522.0611) (3301.7557 4529.8473) (3298.1832 4536.8702) (3292.6107 4542.4427) (3285.5878 4546.0153)
      (3277.8015 4547.2519) (3270.0153 4546.0153) (3262.9924 4542.4427) (3257.4198 4536.8702) (3253.8473 4529.8473)
    ))
    ; P2973 -- see feature_dimensions_mm.csv
    ("06_ORNAMENT" 1 (
      (3252.6107 4317.6336) (3253.8473 4309.8473) (3257.4198 4302.8244) (3262.9924 4297.2519) (3270.0153 4293.6794)
      (3277.8015 4292.4427) (3285.5878 4293.6794) (3292.6107 4297.2519) (3298.1832 4302.8244) (3301.7557 4309.8473)
      (3302.9924 4317.6336) (3301.7557 4325.4198) (3298.1832 4332.4427) (3292.6107 4338.0153) (3285.5878 4341.5878)
      (3277.8015 4342.8244) (3270.0153 4341.5878) (3262.9924 4338.0153) (3257.4198 4332.4427) (3253.8473 4325.4198)
    ))
    ; P2974 -- see feature_dimensions_mm.csv
    ("06_ORNAMENT" 1 (
      (3252.6107 3926.6412) (3253.8473 3918.855) (3257.4198 3911.8321) (3262.9924 3906.2595) (3270.0153 3902.687)
      (3277.8015 3901.4504) (3285.5878 3902.687) (3292.6107 3906.2595) (3298.1832 3911.8321) (3301.7557 3918.855)
      (3302.9924 3926.6412) (3301.7557 3934.4275) (3298.1832 3941.4504) (3292.6107 3947.0229) (3285.5878 3950.5954)
      (3277.8015 3951.8321) (3270.0153 3950.5954) (3262.9924 3947.0229) (3257.4198 3941.4504) (3253.8473 3934.4275)
    ))
    ; P2975 -- see feature_dimensions_mm.csv
    ("06_ORNAMENT" 1 (
      (3298.3206 5312.9771) (3299.4809 5301.1756) (3302.916 5289.8473) (3308.5038 5279.3893) (3316.0305 5270.229)
      (3325.1908 5262.7023) (3335.6489 5257.1145) (3346.9771 5253.6794) (3358.7786 5252.5191) (3370.5802 5253.6794)
      (3381.9084 5257.1145) (3392.3664 5262.7023) (3401.5267 5270.229) (3409.0534 5279.3893) (3414.6412 5289.8473)
      (3418.0763 5301.1756) (3419.2366 5312.9771) (3418.0763 5324.7786) (3414.6412 5336.1069) (3409.0534 5346.5649)
      (3401.5267 5355.7252) (3392.3664 5363.2519) (3381.9084 5368.8397) (3370.5802 5372.2748) (3358.7786 5373.4351)
      (3346.9771 5372.2748) (3335.6489 5368.8397) (3325.1908 5363.2519) (3316.0305 5355.7252) (3308.5038 5346.5649)
      (3302.916 5336.1069) (3299.4809 5324.7786)
    ))
    ; P2976 -- see feature_dimensions_mm.csv
    ("06_ORNAMENT" 1 (
      (3298.3206 4717.5573) (3299.4809 4705.7557) (3302.916 4694.4275) (3308.5038 4683.9695) (3316.0305 4674.8092)
      (3325.1908 4667.2824) (3335.6489 4661.6947) (3346.9771 4658.2595) (3358.7786 4657.0992) (3370.5802 4658.2595)
      (3381.9084 4661.6947) (3392.3664 4667.2824) (3401.5267 4674.8092) (3409.0534 4683.9695) (3414.6412 4694.4275)
      (3418.0763 4705.7557) (3419.2366 4717.5573) (3418.0763 4729.3588) (3414.6412 4740.687) (3409.0534 4751.145)
      (3401.5267 4760.3053) (3392.3664 4767.8321) (3381.9084 4773.4198) (3370.5802 4776.855) (3358.7786 4778.0153)
      (3346.9771 4776.855) (3335.6489 4773.4198) (3325.1908 4767.8321) (3316.0305 4760.3053) (3308.5038 4751.145)
      (3302.916 4740.687) (3299.4809 4729.3588)
    ))
    ; P2977 -- see feature_dimensions_mm.csv
    ("06_ORNAMENT" 1 (
      (3298.3206 4122.1374) (3299.4809 4110.3359) (3302.916 4099.0076) (3308.5038 4088.5496) (3316.0305 4079.3893)
      (3325.1908 4071.8626) (3335.6489 4066.2748) (3346.9771 4062.8397) (3358.7786 4061.6794) (3370.5802 4062.8397)
      (3381.9084 4066.2748) (3392.3664 4071.8626) (3401.5267 4079.3893) (3409.0534 4088.5496) (3414.6412 4099.0076)
      (3418.0763 4110.3359) (3419.2366 4122.1374) (3418.0763 4133.9389) (3414.6412 4145.2672) (3409.0534 4155.7252)
      (3401.5267 4164.8855) (3392.3664 4172.4122) (3381.9084 4178.0) (3370.5802 4181.4351) (3358.7786 4182.5954)
      (3346.9771 4181.4351) (3335.6489 4178.0) (3325.1908 4172.4122) (3316.0305 4164.8855) (3308.5038 4155.7252)
      (3302.916 4145.2672) (3299.4809 4133.9389)
    ))
    ; P2978 -- see feature_dimensions_mm.csv
    ("06_ORNAMENT" 1 (
      (3323.5115 5312.9771) (3324.7176 5303.8473) (3328.229 5295.3435) (3333.8473 5288.0458) (3341.145 5282.4275)
      (3349.6489 5278.916) (3358.7786 5277.7099) (3367.9084 5278.916) (3376.4122 5282.4275) (3383.7099 5288.0458)
      (3389.3282 5295.3435) (3392.8397 5303.8473) (3394.0458 5312.9771) (3392.8397 5322.1069) (3389.3282 5330.6107)
      (3383.7099 5337.9084) (3376.4122 5343.5267) (3367.9084 5347.0382) (3358.7786 5348.2443) (3349.6489 5347.0382)
      (3341.145 5343.5267) (3333.8473 5337.9084) (3328.229 5330.6107) (3324.7176 5322.1069)
    ))
    ; P2979 -- see feature_dimensions_mm.csv
    ("06_ORNAMENT" 1 (
      (3323.5115 4717.5573) (3324.7176 4708.4275) (3328.229 4699.9237) (3333.8473 4692.626) (3341.145 4687.0076)
      (3349.6489 4683.4962) (3358.7786 4682.2901) (3367.9084 4683.4962) (3376.4122 4687.0076) (3383.7099 4692.626)
      (3389.3282 4699.9237) (3392.8397 4708.4275) (3394.0458 4717.5573) (3392.8397 4726.687) (3389.3282 4735.1908)
      (3383.7099 4742.4885) (3376.4122 4748.1069) (3367.9084 4751.6183) (3358.7786 4752.8244) (3349.6489 4751.6183)
      (3341.145 4748.1069) (3333.8473 4742.4885) (3328.229 4735.1908) (3324.7176 4726.687)
    ))
    ; P2980 -- see feature_dimensions_mm.csv
    ("06_ORNAMENT" 1 (
      (3323.5115 4122.1374) (3324.7176 4113.0076) (3328.229 4104.5038) (3333.8473 4097.2061) (3341.145 4091.5878)
      (3349.6489 4088.0763) (3358.7786 4086.8702) (3367.9084 4088.0763) (3376.4122 4091.5878) (3383.7099 4097.2061)
      (3389.3282 4104.5038) (3392.8397 4113.0076) (3394.0458 4122.1374) (3392.8397 4131.2672) (3389.3282 4139.771)
      (3383.7099 4147.0687) (3376.4122 4152.687) (3367.9084 4156.1985) (3358.7786 4157.4046) (3349.6489 4156.1985)
      (3341.145 4152.687) (3333.8473 4147.0687) (3328.229 4139.771) (3324.7176 4131.2672)
    ))
    ; P2981 -- see feature_dimensions_mm.csv
    ("06_ORNAMENT" 1 (
      (3326.0305 5181.9847) (3326.4275 5172.916) (3327.6336 5164.0763) (3329.6031 5155.6794) (3332.2901 5147.9237)
      (3335.6183 5141.0229) (3339.5267 5135.1145) (3343.9084 5130.3664) (3348.6565 5126.8855) (3353.6489 5124.7634)
      (3358.7786 5124.0458) (3363.9084 5124.7634) (3368.9008 5126.8855) (3373.6489 5130.3664) (3378.0305 5135.1145)
      (3381.9389 5141.0229) (3385.2672 5147.9237) (3387.9542 5155.6794) (3389.9237 5164.0763) (3391.1298 5172.916)
      (3391.5267 5181.9847) (3391.1298 5191.0534) (3389.9237 5199.8931) (3387.9542 5208.2901) (3385.2672 5216.0458)
      (3381.9389 5222.9466) (3378.0305 5228.855) (3373.6489 5233.6031) (3368.9008 5237.084) (3363.9084 5239.2061)
      (3358.7786 5239.9237) (3353.6489 5239.2061) (3348.6565 5237.084) (3343.9084 5233.6031) (3339.5267 5228.855)
      (3335.6183 5222.9466) (3332.2901 5216.0458) (3329.6031 5208.2901) (3327.6336 5199.8931) (3326.4275 5191.0534)
    ))
    ; P2982 -- see feature_dimensions_mm.csv
    ("06_ORNAMENT" 1 (
      (3326.0305 4848.5496) (3326.4275 4839.4809) (3327.6336 4830.6412) (3329.6031 4822.2443) (3332.2901 4814.4885)
      (3335.6183 4807.5878) (3339.5267 4801.6794) (3343.9084 4796.9313) (3348.6565 4793.4504) (3353.6489 4791.3282)
      (3358.7786 4790.6107) (3363.9084 4791.3282) (3368.9008 4793.4504) (3373.6489 4796.9313) (3378.0305 4801.6794)
      (3381.9389 4807.5878) (3385.2672 4814.4885) (3387.9542 4822.2443) (3389.9237 4830.6412) (3391.1298 4839.4809)
      (3391.5267 4848.5496) (3391.1298 4857.6183) (3389.9237 4866.458) (3387.9542 4874.855) (3385.2672 4882.6107)
      (3381.9389 4889.5115) (3378.0305 4895.4198) (3373.6489 4900.1679) (3368.9008 4903.6489) (3363.9084 4905.771)
      (3358.7786 4906.4885) (3353.6489 4905.771) (3348.6565 4903.6489) (3343.9084 4900.1679) (3339.5267 4895.4198)
      (3335.6183 4889.5115) (3332.2901 4882.6107) (3329.6031 4874.855) (3327.6336 4866.458) (3326.4275 4857.6183)
    ))
    ; P2983 -- see feature_dimensions_mm.csv
    ("06_ORNAMENT" 1 (
      (3326.0305 4253.1298) (3326.4275 4244.0611) (3327.6336 4235.2214) (3329.6031 4226.8244) (3332.2901 4219.0687)
      (3335.6183 4212.1679) (3339.5267 4206.2595) (3343.9084 4201.5115) (3348.6565 4198.0305) (3353.6489 4195.9084)
      (3358.7786 4195.1908) (3363.9084 4195.9084) (3368.9008 4198.0305) (3373.6489 4201.5115) (3378.0305 4206.2595)
      (3381.9389 4212.1679) (3385.2672 4219.0687) (3387.9542 4226.8244) (3389.9237 4235.2214) (3391.1298 4244.0611)
      (3391.5267 4253.1298) (3391.1298 4262.1985) (3389.9237 4271.0382) (3387.9542 4279.4351) (3385.2672 4287.1908)
      (3381.9389 4294.0916) (3378.0305 4300.0) (3373.6489 4304.7481) (3368.9008 4308.229) (3363.9084 4310.3511)
      (3358.7786 4311.0687) (3353.6489 4310.3511) (3348.6565 4308.229) (3343.9084 4304.7481) (3339.5267 4300.0)
      (3335.6183 4294.0916) (3332.2901 4287.1908) (3329.6031 4279.4351) (3327.6336 4271.0382) (3326.4275 4262.1985)
    ))
    ; P2984 -- see feature_dimensions_mm.csv
    ("06_ORNAMENT" 1 (
      (3326.0305 3991.145) (3326.4275 3982.0763) (3327.6336 3973.2366) (3329.6031 3964.8397) (3332.2901 3957.084)
      (3335.6183 3950.1832) (3339.5267 3944.2748) (3343.9084 3939.5267) (3348.6565 3936.0458) (3353.6489 3933.9237)
      (3358.7786 3933.2061) (3363.9084 3933.9237) (3368.9008 3936.0458) (3373.6489 3939.5267) (3378.0305 3944.2748)
      (3381.9389 3950.1832) (3385.2672 3957.084) (3387.9542 3964.8397) (3389.9237 3973.2366) (3391.1298 3982.0763)
      (3391.5267 3991.145) (3391.1298 4000.2137) (3389.9237 4009.0534) (3387.9542 4017.4504) (3385.2672 4025.2061)
      (3381.9389 4032.1069) (3378.0305 4038.0153) (3373.6489 4042.7634) (3368.9008 4046.2443) (3363.9084 4048.3664)
      (3358.7786 4049.084) (3353.6489 4048.3664) (3348.6565 4046.2443) (3343.9084 4042.7634) (3339.5267 4038.0153)
      (3335.6183 4032.1069) (3332.2901 4025.2061) (3329.6031 4017.4504) (3327.6336 4009.0534) (3326.4275 4000.2137)
    ))
    ; P2985 -- see feature_dimensions_mm.csv
    ("06_ORNAMENT" 1 (
      (3347.4504 5048.4733) (3348.9618 5042.8092) (3353.1145 5038.6565) (3358.7786 5037.1298) (3364.4427 5038.6565)
      (3368.5954 5042.8092) (3370.1221 5048.4733) (3368.5954 5054.1374) (3364.4427 5058.2901) (3358.7786 5059.8015)
      (3353.1145 5058.2901) (3348.9618 5054.1374)
    ))
    ; P2986 -- see feature_dimensions_mm.csv
    ("06_ORNAMENT" 1 (
      (3347.4504 3857.6336) (3348.9618 3851.9695) (3353.1145 3847.8168) (3358.7786 3846.2901) (3364.4427 3847.8168)
      (3368.5954 3851.9695) (3370.1221 3857.6336) (3368.5954 3863.2977) (3364.4427 3867.4504) (3358.7786 3868.9618)
      (3353.1145 3867.4504) (3348.9618 3863.2977)
    ))
    ; P2987 -- see feature_dimensions_mm.csv
    ("06_ORNAMENT" 1 (
      (3383.8168 3007.6336) (3384.5344 3006.3206) (3386.458 3005.2519) (3389.0992 3004.5496) (3391.7405 3004.1985)
      (3393.7252 3003.9542) (3394.6107 3003.4962) (3394.3053 3002.5649) (3393.0687 3000.9924) (3391.4656 2998.8702)
      (3390.0916 2996.5038) (3389.4656 2994.3817) (3389.8931 2992.9466) (3391.3282 2992.5191) (3393.4504 2993.145)
      (3395.8168 2994.5191) (3397.9389 2996.1221) (3399.5115 2997.3588) (3400.4427 2997.6641) (3400.9008 2996.7786)
      (3401.145 2994.7939) (3401.4962 2992.1527) (3402.1985 2989.5115) (3403.2672 2987.5878) (3404.5802 2986.8702)
      (3405.8931 2987.5878) (3406.9618 2989.5115) (3407.6641 2992.1527) (3408.0153 2994.7939) (3408.2595 2996.7786)
      (3408.7176 2997.6641) (3409.6489 2997.3588) (3411.2214 2996.1221) (3413.3435 2994.5191) (3415.7099 2993.145)
      (3417.8321 2992.5191) (3419.2672 2992.9466) (3419.6947 2994.3817) (3419.0687 2996.5038) (3417.6947 2998.8702)
      (3416.0916 3000.9924) (3414.855 3002.5649) (3414.5496 3003.4962) (3415.4351 3003.9542) (3417.4198 3004.1985)
      (3420.0611 3004.5496) (3422.7023 3005.2519) (3424.626 3006.3206) (3425.3435 3007.6336) (3424.626 3008.9466)
      (3422.7023 3010.0153) (3420.0611 3010.7176) (3417.4198 3011.0687) (3415.4351 3011.313) (3414.5496 3011.771)
      (3414.855 3012.7023) (3416.0916 3014.2748) (3417.6947 3016.3969) (3419.0687 3018.7634) (3419.6947 3020.8855)
      (3419.2672 3022.3206) (3417.8321 3022.7481) (3415.7099 3022.1221) (3413.3435 3020.7481) (3411.2214 3019.145)
      (3409.6489 3017.9084) (3408.7176 3017.6031) (3408.2595 3018.4885) (3408.0153 3020.4733) (3407.6641 3023.1145)
      (3406.9618 3025.7557) (3405.8931 3027.6794) (3404.5802 3028.3969) (3403.2672 3027.6794) (3402.1985 3025.7557)
      (3401.4962 3023.1145) (3401.145 3020.4733) (3400.9008 3018.4885) (3400.4427 3017.6031) (3399.5115 3017.9084)
      (3397.9389 3019.145) (3395.8168 3020.7481) (3393.4504 3022.1221) (3391.3282 3022.7481) (3389.8931 3022.3206)
      (3389.4656 3020.8855) (3390.0916 3018.7634) (3391.4656 3016.3969) (3393.0687 3014.2748) (3394.3053 3012.7023)
      (3394.6107 3011.771) (3393.7252 3011.313) (3391.7405 3011.0687) (3389.0992 3010.7176) (3386.458 3010.0153)
      (3384.5344 3008.9466)
    ))
    ; P2988 -- see feature_dimensions_mm.csv
    ("06_ORNAMENT" 1 (
      (3383.8168 2900.7634) (3384.5344 2899.4504) (3386.458 2898.3817) (3389.0992 2897.6794) (3391.7405 2897.3282)
      (3393.7252 2897.084) (3394.6107 2896.626) (3394.3053 2895.6947) (3393.0687 2894.1221) (3391.4656 2892.0)
      (3390.0916 2889.6336) (3389.4656 2887.5115) (3389.8931 2886.0763) (3391.3282 2885.6489) (3393.4504 2886.2748)
      (3395.8168 2887.6489) (3397.9389 2889.2519) (3399.5115 2890.4885) (3400.4427 2890.7939) (3400.9008 2889.9084)
      (3401.145 2887.9237) (3401.4962 2885.2824) (3402.1985 2882.6412) (3403.2672 2880.7176) (3404.5802 2880.0)
      (3405.8931 2880.7176) (3406.9618 2882.6412) (3407.6641 2885.2824) (3408.0153 2887.9237) (3408.2595 2889.9084)
      (3408.7176 2890.7939) (3409.6489 2890.4885) (3411.2214 2889.2519) (3413.3435 2887.6489) (3415.7099 2886.2748)
      (3417.8321 2885.6489) (3419.2672 2886.0763) (3419.6947 2887.5115) (3419.0687 2889.6336) (3417.6947 2892.0)
      (3416.0916 2894.1221) (3414.855 2895.6947) (3414.5496 2896.626) (3415.4351 2897.084) (3417.4198 2897.3282)
      (3420.0611 2897.6794) (3422.7023 2898.3817) (3424.626 2899.4504) (3425.3435 2900.7634) (3424.626 2902.0763)
      (3422.7023 2903.145) (3420.0611 2903.8473) (3417.4198 2904.1985) (3415.4351 2904.4427) (3414.5496 2904.9008)
      (3414.855 2905.8321) (3416.0916 2907.4046) (3417.6947 2909.5267) (3419.0687 2911.8931) (3419.6947 2914.0153)
      (3419.2672 2915.4504) (3417.8321 2915.8779) (3415.7099 2915.2519) (3413.3435 2913.8779) (3411.2214 2912.2748)
      (3409.6489 2911.0382) (3408.7176 2910.7328) (3408.2595 2911.6183) (3408.0153 2913.6031) (3407.6641 2916.2443)
      (3406.9618 2918.8855) (3405.8931 2920.8092) (3404.5802 2921.5267) (3403.2672 2920.8092) (3402.1985 2918.8855)
      (3401.4962 2916.2443) (3401.145 2913.6031) (3400.9008 2911.6183) (3400.4427 2910.7328) (3399.5115 2911.0382)
      (3397.9389 2912.2748) (3395.8168 2913.8779) (3393.4504 2915.2519) (3391.3282 2915.8779) (3389.8931 2915.4504)
      (3389.4656 2914.0153) (3390.0916 2911.8931) (3391.4656 2909.5267) (3393.0687 2907.4046) (3394.3053 2905.8321)
      (3394.6107 2904.9008) (3393.7252 2904.4427) (3391.7405 2904.1985) (3389.0992 2903.8473) (3386.458 2903.145)
      (3384.5344 2902.0763)
    ))
    ; P2989 -- see feature_dimensions_mm.csv
    ("06_ORNAMENT" 1 (
      (3398.4733 3007.6336) (3398.9313 3005.2977) (3400.2595 3003.313) (3402.2443 3001.9847) (3404.5802 3001.5267)
      (3406.916 3001.9847) (3408.9008 3003.313) (3410.229 3005.2977) (3410.687 3007.6336) (3410.229 3009.9695)
      (3408.9008 3011.9542) (3406.916 3013.2824) (3404.5802 3013.7405) (3402.2443 3013.2824) (3400.2595 3011.9542)
      (3398.9313 3009.9695)
    ))
    ; P2990 -- see feature_dimensions_mm.csv
    ("06_ORNAMENT" 1 (
      (3398.4733 2900.7634) (3398.9313 2898.4275) (3400.2595 2896.4427) (3402.2443 2895.1145) (3404.5802 2894.6565)
      (3406.916 2895.1145) (3408.9008 2896.4427) (3410.229 2898.4275) (3410.687 2900.7634) (3410.229 2903.0992)
      (3408.9008 2905.084) (3406.916 2906.4122) (3404.5802 2906.8702) (3402.2443 2906.4122) (3400.2595 2905.084)
      (3398.9313 2903.0992)
    ))
    ; P2991 -- see feature_dimensions_mm.csv
    ("06_ORNAMENT" 1 (
      (3404.3817 5246.3359) (3404.6412 5239.8779) (3406.0611 5232.9466) (3408.5954 5225.6947) (3412.1679 5218.3206)
      (3416.7176 5210.9924) (3422.1221 5203.8931) (3428.2443 5197.1908) (3434.9466 5191.0687) (3442.0458 5185.6641)
      (3449.374 5181.1145) (3456.7481 5177.542) (3464.0 5175.0076) (3470.9313 5173.6031) (3477.3893 5173.3282)
      (3483.2061 5174.229) (3488.2443 5176.2595) (3492.3664 5179.3893) (3495.4962 5183.5115) (3497.5267 5188.5496)
      (3498.4275 5194.3664) (3498.1527 5200.8244) (3496.7481 5207.7557) (3494.2137 5215.0076) (3490.6412 5222.3817)
      (3486.0916 5229.7099) (3480.687 5236.8092) (3474.5649 5243.5115) (3467.8626 5249.6336) (3460.7634 5255.0382)
      (3453.4351 5259.5878) (3446.0611 5263.1603) (3438.8092 5265.6947) (3431.8779 5267.1145) (3425.4198 5267.374)
      (3419.6031 5266.4733) (3414.5649 5264.4427) (3410.4427 5261.313) (3407.313 5257.1908) (3405.2824 5252.1527)
    ))
    ; P2992 -- see feature_dimensions_mm.csv
    ("06_ORNAMENT" 1 (
      (3404.3817 4784.1985) (3405.2824 4778.3817) (3407.313 4773.3435) (3410.4427 4769.2214) (3414.5649 4766.0916)
      (3419.6031 4764.0611) (3425.4198 4763.1603) (3431.8779 4763.4198) (3438.8092 4764.8397) (3446.0611 4767.374)
      (3453.4351 4770.9466) (3460.7634 4775.4962) (3467.8626 4780.9008) (3474.5649 4787.0229) (3480.687 4793.7252)
      (3486.0916 4800.8244) (3490.6412 4808.1527) (3494.2137 4815.5267) (3496.7481 4822.7786) (3498.1527 4829.7099)
      (3498.4275 4836.1679) (3497.5267 4841.9847) (3495.4962 4847.0229) (3492.3664 4851.145) (3488.2443 4854.2748)
      (3483.2061 4856.3053) (3477.3893 4857.2061) (3470.9313 4856.9313) (3464.0 4855.5267) (3456.7481 4852.9924)
      (3449.374 4849.4198) (3442.0458 4844.8702) (3434.9466 4839.4656) (3428.2443 4833.3435) (3422.1221 4826.6412)
      (3416.7176 4819.542) (3412.1679 4812.2137) (3408.5954 4804.8397) (3406.0611 4797.5878) (3404.6412 4790.6565)
    ))
    ; P2993 -- see feature_dimensions_mm.csv
    ("06_ORNAMENT" 1 (
      (3404.3817 4650.916) (3404.6412 4644.458) (3406.0611 4637.5267) (3408.5954 4630.2748) (3412.1679 4622.9008)
      (3416.7176 4615.5725) (3422.1221 4608.4733) (3428.2443 4601.771) (3434.9466 4595.6489) (3442.0458 4590.2443)
      (3449.374 4585.6947) (3456.7481 4582.1221) (3464.0 4579.5878) (3470.9313 4578.1832) (3477.3893 4577.9084)
      (3483.2061 4578.8092) (3488.2443 4580.8397) (3492.3664 4583.9695) (3495.4962 4588.0916) (3497.5267 4593.1298)
      (3498.4275 4598.9466) (3498.1527 4605.4046) (3496.7481 4612.3359) (3494.2137 4619.5878) (3490.6412 4626.9618)
      (3486.0916 4634.2901) (3480.687 4641.3893) (3474.5649 4648.0916) (3467.8626 4654.2137) (3460.7634 4659.6183)
      (3453.4351 4664.1679) (3446.0611 4667.7405) (3438.8092 4670.2748) (3431.8779 4671.6947) (3425.4198 4671.9542)
      (3419.6031 4671.0534) (3414.5649 4669.0229) (3410.4427 4665.8931) (3407.313 4661.771) (3405.2824 4656.7328)
    ))
    ; P2994 -- see feature_dimensions_mm.csv
    ("06_ORNAMENT" 1 (
      (3404.3817 4188.7786) (3405.2824 4182.9618) (3407.313 4177.9237) (3410.4427 4173.8015) (3414.5649 4170.6718)
      (3419.6031 4168.6412) (3425.4198 4167.7405) (3431.8779 4168.0) (3438.8092 4169.4198) (3446.0611 4171.9542)
      (3453.4351 4175.5267) (3460.7634 4180.0763) (3467.8626 4185.4809) (3474.5649 4191.6031) (3480.687 4198.3053)
      (3486.0916 4205.4046) (3490.6412 4212.7328) (3494.2137 4220.1069) (3496.7481 4227.3588) (3498.1527 4234.2901)
      (3498.4275 4240.7481) (3497.5267 4246.5649) (3495.4962 4251.6031) (3492.3664 4255.7252) (3488.2443 4258.855)
      (3483.2061 4260.8855) (3477.3893 4261.7863) (3470.9313 4261.5115) (3464.0 4260.1069) (3456.7481 4257.5725)
      (3449.374 4254.0) (3442.0458 4249.4504) (3434.9466 4244.0458) (3428.2443 4237.9237) (3422.1221 4231.2214)
      (3416.7176 4224.1221) (3412.1679 4216.7939) (3408.5954 4209.4198) (3406.0611 4202.1679) (3404.6412 4195.2366)
    ))
    ; P2995 -- see feature_dimensions_mm.csv
    ("06_ORNAMENT" 1 (
      (3404.3817 4055.4962) (3404.6412 4049.0382) (3406.0611 4042.1069) (3408.5954 4034.855) (3412.1679 4027.4809)
      (3416.7176 4020.1527) (3422.1221 4013.0534) (3428.2443 4006.3511) (3434.9466 4000.229) (3442.0458 3994.8244)
      (3449.374 3990.2748) (3456.7481 3986.7023) (3464.0 3984.1679) (3470.9313 3982.7634) (3477.3893 3982.4885)
      (3483.2061 3983.3893) (3488.2443 3985.4198) (3492.3664 3988.5496) (3495.4962 3992.6718) (3497.5267 3997.7099)
      (3498.4275 4003.5267) (3498.1527 4009.9847) (3496.7481 4016.916) (3494.2137 4024.1679) (3490.6412 4031.542)
      (3486.0916 4038.8702) (3480.687 4045.9695) (3474.5649 4052.6718) (3467.8626 4058.7939) (3460.7634 4064.1985)
      (3453.4351 4068.7481) (3446.0611 4072.3206) (3438.8092 4074.855) (3431.8779 4076.2748) (3425.4198 4076.5344)
      (3419.6031 4075.6336) (3414.5649 4073.6031) (3410.4427 4070.4733) (3407.313 4066.3511) (3405.2824 4061.313)
    ))
    ; P2996 -- see feature_dimensions_mm.csv
    ("06_ORNAMENT" 1 (
      (3414.5649 5117.4809) (3415.8015 5109.6947) (3419.374 5102.6718) (3424.9466 5097.0992) (3431.9695 5093.5267)
      (3439.7557 5092.2901) (3447.542 5093.5267) (3454.5649 5097.0992) (3460.1374 5102.6718) (3463.7099 5109.6947)
      (3464.9466 5117.4809) (3463.7099 5125.2672) (3460.1374 5132.2901) (3454.5649 5137.8626) (3447.542 5141.4351)
      (3439.7557 5142.6718) (3431.9695 5141.4351) (3424.9466 5137.8626) (3419.374 5132.2901) (3415.8015 5125.2672)
    ))
    ; P2997 -- see feature_dimensions_mm.csv
    ("06_ORNAMENT" 1 (
      (3414.5649 4913.0534) (3415.8015 4905.2672) (3419.374 4898.2443) (3424.9466 4892.6718) (3431.9695 4889.0992)
      (3439.7557 4887.8626) (3447.542 4889.0992) (3454.5649 4892.6718) (3460.1374 4898.2443) (3463.7099 4905.2672)
      (3464.9466 4913.0534) (3463.7099 4920.8397) (3460.1374 4927.8626) (3454.5649 4933.4351) (3447.542 4937.0076)
      (3439.7557 4938.2443) (3431.9695 4937.0076) (3424.9466 4933.4351) (3419.374 4927.8626) (3415.8015 4920.8397)
    ))
    ; P2998 -- see feature_dimensions_mm.csv
    ("06_ORNAMENT" 1 (
      (3414.5649 4522.0611) (3415.8015 4514.2748) (3419.374 4507.2519) (3424.9466 4501.6794) (3431.9695 4498.1069)
      (3439.7557 4496.8702) (3447.542 4498.1069) (3454.5649 4501.6794) (3460.1374 4507.2519) (3463.7099 4514.2748)
      (3464.9466 4522.0611) (3463.7099 4529.8473) (3460.1374 4536.8702) (3454.5649 4542.4427) (3447.542 4546.0153)
      (3439.7557 4547.2519) (3431.9695 4546.0153) (3424.9466 4542.4427) (3419.374 4536.8702) (3415.8015 4529.8473)
    ))
    ; P2999 -- see feature_dimensions_mm.csv
    ("06_ORNAMENT" 1 (
      (3414.5649 4317.6336) (3415.8015 4309.8473) (3419.374 4302.8244) (3424.9466 4297.2519) (3431.9695 4293.6794)
      (3439.7557 4292.4427) (3447.542 4293.6794) (3454.5649 4297.2519) (3460.1374 4302.8244) (3463.7099 4309.8473)
      (3464.9466 4317.6336) (3463.7099 4325.4198) (3460.1374 4332.4427) (3454.5649 4338.0153) (3447.542 4341.5878)
      (3439.7557 4342.8244) (3431.9695 4341.5878) (3424.9466 4338.0153) (3419.374 4332.4427) (3415.8015 4325.4198)
    ))
    ; P3000 -- see feature_dimensions_mm.csv
    ("06_ORNAMENT" 1 (
      (3414.5649 3926.6412) (3415.8015 3918.855) (3419.374 3911.8321) (3424.9466 3906.2595) (3431.9695 3902.687)
      (3439.7557 3901.4504) (3447.542 3902.687) (3454.5649 3906.2595) (3460.1374 3911.8321) (3463.7099 3918.855)
      (3464.9466 3926.6412) (3463.7099 3934.4275) (3460.1374 3941.4504) (3454.5649 3947.0229) (3447.542 3950.5954)
      (3439.7557 3951.8321) (3431.9695 3950.5954) (3424.9466 3947.0229) (3419.374 3941.4504) (3415.8015 3934.4275)
    ))
    ; P3001 -- see feature_dimensions_mm.csv
    ("06_ORNAMENT" 1 (
      (3431.8321 5312.9771) (3432.5496 5307.8473) (3434.6718 5302.855) (3438.1527 5298.1069) (3442.9008 5293.7252)
      (3448.8092 5289.8168) (3455.7099 5286.4885) (3463.4656 5283.8015) (3471.8626 5281.8321) (3480.7023 5280.626)
      (3489.771 5280.229) (3498.8397 5280.626) (3507.6794 5281.8321) (3516.0763 5283.8015) (3523.8321 5286.4885)
      (3530.7328 5289.8168) (3536.6412 5293.7252) (3541.3893 5298.1069) (3544.8702 5302.855) (3546.9924 5307.8473)
      (3547.7099 5312.9771) (3546.9924 5318.1069) (3544.8702 5323.0992) (3541.3893 5327.8473) (3536.6412 5332.229)
      (3530.7328 5336.1374) (3523.8321 5339.4656) (3516.0763 5342.1527) (3507.6794 5344.1221) (3498.8397 5345.3282)
      (3489.771 5345.7252) (3480.7023 5345.3282) (3471.8626 5344.1221) (3463.4656 5342.1527) (3455.7099 5339.4656)
      (3448.8092 5336.1374) (3442.9008 5332.229) (3438.1527 5327.8473) (3434.6718 5323.0992) (3432.5496 5318.1069)
    ))
    ; P3002 -- see feature_dimensions_mm.csv
    ("06_ORNAMENT" 1 (
      (3431.8321 4717.5573) (3432.5496 4712.4275) (3434.6718 4707.4351) (3438.1527 4702.687) (3442.9008 4698.3053)
      (3448.8092 4694.3969) (3455.7099 4691.0687) (3463.4656 4688.3817) (3471.8626 4686.4122) (3480.7023 4685.2061)
      (3489.771 4684.8092) (3498.8397 4685.2061) (3507.6794 4686.4122) (3516.0763 4688.3817) (3523.8321 4691.0687)
      (3530.7328 4694.3969) (3536.6412 4698.3053) (3541.3893 4702.687) (3544.8702 4707.4351) (3546.9924 4712.4275)
      (3547.7099 4717.5573) (3546.9924 4722.687) (3544.8702 4727.6794) (3541.3893 4732.4275) (3536.6412 4736.8092)
      (3530.7328 4740.7176) (3523.8321 4744.0458) (3516.0763 4746.7328) (3507.6794 4748.7023) (3498.8397 4749.9084)
      (3489.771 4750.3053) (3480.7023 4749.9084) (3471.8626 4748.7023) (3463.4656 4746.7328) (3455.7099 4744.0458)
      (3448.8092 4740.7176) (3442.9008 4736.8092) (3438.1527 4732.4275) (3434.6718 4727.6794) (3432.5496 4722.687)
    ))
    ; P3003 -- see feature_dimensions_mm.csv
    ("06_ORNAMENT" 1 (
      (3431.8321 4122.1374) (3432.5496 4117.0076) (3434.6718 4112.0153) (3438.1527 4107.2672) (3442.9008 4102.8855)
      (3448.8092 4098.9771) (3455.7099 4095.6489) (3463.4656 4092.9618) (3471.8626 4090.9924) (3480.7023 4089.7863)
      (3489.771 4089.3893) (3498.8397 4089.7863) (3507.6794 4090.9924) (3516.0763 4092.9618) (3523.8321 4095.6489)
      (3530.7328 4098.9771) (3536.6412 4102.8855) (3541.3893 4107.2672) (3544.8702 4112.0153) (3546.9924 4117.0076)
      (3547.7099 4122.1374) (3546.9924 4127.2672) (3544.8702 4132.2595) (3541.3893 4137.0076) (3536.6412 4141.3893)
      (3530.7328 4145.2977) (3523.8321 4148.626) (3516.0763 4151.313) (3507.6794 4153.2824) (3498.8397 4154.4885)
      (3489.771 4154.8855) (3480.7023 4154.4885) (3471.8626 4153.2824) (3463.4656 4151.313) (3455.7099 4148.626)
      (3448.8092 4145.2977) (3442.9008 4141.3893) (3438.1527 4137.0076) (3434.6718 4132.2595) (3432.5496 4127.2672)
    ))
    ; P3004 -- see feature_dimensions_mm.csv
    ("06_ORNAMENT" 1 (
      (3435.1145 5969.4656) (3466.5802 5968.9924) (3499.8626 5971.3435) (3534.5191 5976.2595) (3570.0916 5983.4656)
      (3606.1527 5992.687) (3642.2137 6003.6641) (3677.8779 6016.1069) (3712.6565 6029.771) (3746.1069 6044.3817)
      (3777.8015 6059.6641) (3807.2672 6075.3435) (3815.9695 6080.4885) (3812.6565 6077.5267) (3805.1603 6069.374)
      (3798.855 6060.7786) (3793.8931 6051.9084) (3789.3282 6041.8779) (3784.5802 6030.1985) (3780.3969 6017.542)
      (3777.5115 6004.5802) (3776.6718 5992.0) (3778.626 5980.4885) (3784.1221 5970.7176) (3793.8931 5963.3588)
      (3810.9618 5958.4275) (3835.9237 5955.2519) (3865.8626 5953.5573) (3897.8779 5953.0534) (3929.0534 5953.4656)
      (3956.4885 5954.4885) (3977.2977 5955.8473) (3988.5496 5957.2519) (3989.084 5958.9771) (3981.1756 5961.4046)
      (3967.0534 5964.4275) (3948.9771 5967.9389) (3929.1908 5971.8321) (3909.9542 5976.0) (3893.5267 5980.3359)
      (3882.1374 5984.7328) (3874.8397 5989.4046) (3869.0534 5994.5649) (3864.6718 6000.0458) (3861.542 6005.7252)
      (3859.5115 6011.4504) (3858.4733 6017.084) (3858.2748 6022.4733) (3858.7786 6027.4809) (3860.3053 6032.3511)
      (3863.1145 6037.3435) (3867.0076 6042.2901) (3871.7557 6047.0382) (3877.1603 6051.4504) (3882.9924 6055.3588)
      (3889.0534 6058.6107) (3895.1145 6061.0687) (3902.1221 6062.687) (3910.6412 6063.5878) (3920.0153 6063.8779)
      (3929.5115 6063.6489) (3938.4275 6062.9924) (3946.0916 6062.0305) (3951.7863 6060.855) (3954.8092 6059.542)
      (3954.3511 6057.9847) (3950.7176 6056.0458) (3944.916 6053.771) (3937.9389 6051.2366) (3930.8092 6048.5038)
      (3924.5191 6045.6183) (3920.0763 6042.6718) (3918.4733 6039.6947) (3919.5267 6036.3359) (3922.1832 6032.3969)
      (3926.1985 6028.1374) (3931.2824 6023.8473) (3937.2214 6019.8321) (3943.7252 6016.3664) (3950.5344 6013.7252)
      (3957.4046 6012.2137) (3965.0076 6011.771) (3973.8931 6012.1069) (3983.5725 6013.145) (3993.5725 6014.7939)
      (4003.4504 6016.9771) (4012.7023 6019.6183) (4020.8702 6022.6412) (4027.4809 6025.9542) (4033.145 6029.8168)
      (4038.5649 6034.4275) (4043.4351 6039.6031) (4047.4351 6045.1298) (4050.229 6050.8397) (4051.5115 6056.5496)
      (4050.9466 6062.0611) (4048.2443 6067.1756) (4042.9771 6072.1985) (4035.2672 6077.4504) (4025.6183 6082.7328)
      (4014.5038 6087.8779) (4002.4122 6092.7328) (3989.8473 6097.1298) (3977.2824 6100.8702) (3965.1908 6103.8168)
      (3952.9618 6106.1985) (3939.8473 6108.3053) (3926.1832 6109.9695) (3912.3053 6111.0687) (3898.5496 6111.4504)
      (3885.2672 6110.9771) (3872.7481 6109.4962) (3861.374 6106.8702) (3853.3893 6103.9695) (3857.7405 6106.855)
      (3877.8626 6122.1374) (3850.0153 6120.8855) (3819.6336 6117.9237) (3787.2061 6113.313) (3763.7099 6109.0382)
      (3765.5115 6110.7634) (3769.8015 6115.9389) (3773.3282 6121.4656) (3775.8015 6127.1756) (3776.9313 6132.8855)
      (3776.4427 6138.3969) (3774.0458 6143.5115) (3769.3893 6148.5344) (3762.5954 6153.7863) (3754.0763 6159.0687)
      (3744.2748 6164.2137) (3733.6183 6169.0687) (3722.5191 6173.4656) (3711.4198 6177.2061) (3700.7634 6180.1527)
      (3689.9695 6182.5344) (3678.3969 6184.6412) (3666.3511 6186.3053) (3654.1069 6187.4046) (3641.9695 6187.7863)
      (3630.229 6187.313) (3619.2061 6185.8321) (3609.1603 6183.2061) (3599.771 6179.3435) (3590.626 6174.3359)
      (3581.8626 6168.3206) (3573.6641 6161.4504) (3566.1832 6153.8626) (3559.5725 6145.7099) (3554.0 6137.1145)
      (3549.6183 6128.2443) (3545.5878 6118.2137) (3541.4046 6106.5344) (3537.7099 6093.8779) (3535.1603 6080.916)
      (3534.4275 6068.3359) (3536.1527 6056.8244) (3540.9924 6047.0534) (3547.8015 6041.2519) (3543.8473 6039.4962)
      (3512.626 6023.6794) (3483.771 6006.687) (3457.771 5988.5954)
    ))
    ; P3005 -- see feature_dimensions_mm.csv
    ("06_ORNAMENT" 1 (
      (3448.6565 5068.6107) (3450.1832 5062.9466) (3454.3359 5058.7939) (3460.0 5057.2672) (3465.6641 5058.7939)
      (3469.8168 5062.9466) (3471.3282 5068.6107) (3469.8168 5074.2748) (3465.6641 5078.4275) (3460.0 5079.9389)
      (3454.3359 5078.4275) (3450.1832 5074.2748)
    ))
    ; P3006 -- see feature_dimensions_mm.csv
    ("06_ORNAMENT" 1 (
      (3448.6565 4961.9237) (3450.1832 4956.2595) (3454.3359 4952.1069) (3460.0 4950.5954) (3465.6641 4952.1069)
      (3469.8168 4956.2595) (3471.3282 4961.9237) (3469.8168 4967.5878) (3465.6641 4971.7405) (3460.0 4973.2672)
      (3454.3359 4971.7405) (3450.1832 4967.5878)
    ))
    ; P3007 -- see feature_dimensions_mm.csv
    ("06_ORNAMENT" 1 (
      (3448.6565 4366.5038) (3450.1832 4360.8397) (3454.3359 4356.687) (3460.0 4355.1756) (3465.6641 4356.687)
      (3469.8168 4360.8397) (3471.3282 4366.5038) (3469.8168 4372.1679) (3465.6641 4376.3206) (3460.0 4377.8473)
      (3454.3359 4376.3206) (3450.1832 4372.1679)
    ))
    ; P3008 -- see feature_dimensions_mm.csv
    ("06_ORNAMENT" 1 (
      (3448.6565 3877.771) (3450.1832 3872.1069) (3454.3359 3867.9542) (3460.0 3866.4275) (3465.6641 3867.9542)
      (3469.8168 3872.1069) (3471.3282 3877.771) (3469.8168 3883.4351) (3465.6641 3887.5878) (3460.0 3889.0992)
      (3454.3359 3887.5878) (3450.1832 3883.4351)
    ))
    ; P3009 -- see feature_dimensions_mm.csv
    ("06_ORNAMENT" 1 (
      (3456.4885 5022.9008) (3456.9008 5020.3206) (3458.0916 5017.8931) (3459.9847 5015.6947) (3462.4427 5013.8626)
      (3465.2824 5012.4122) (3468.3053 5011.3588) (3471.3435 5010.6412) (3474.1832 5010.1985) (3476.7023 5009.8779)
      (3478.7939 5009.5573) (3480.4275 5009.084) (3481.5878 5008.3053) (3482.3664 5007.145) (3482.8397 5005.5115)
      (3483.1603 5003.4198) (3483.4809 5000.9008) (3483.9237 4998.0611) (3484.6412 4995.0229) (3485.6947 4992.0)
      (3487.145 4989.1603) (3488.9771 4986.7023) (3491.1756 4984.8092) (3493.6031 4983.6183) (3496.1832 4983.2061)
      (3498.7634 4983.6183) (3501.1908 4984.8092) (3503.3893 4986.7023) (3505.2214 4989.1603) (3506.6718 4992.0)
      (3507.7252 4995.0229) (3508.4427 4998.0611) (3508.8855 5000.9008) (3509.2061 5003.4198) (3509.5267 5005.5115)
      (3510.0 5007.145) (3510.7786 5008.3053) (3511.9389 5009.084) (3513.5725 5009.5573) (3515.6641 5009.8779)
      (3518.1832 5010.1985) (3521.0229 5010.6412) (3524.0611 5011.3588) (3527.084 5012.4122) (3529.9237 5013.8626)
      (3532.3817 5015.6947) (3534.2748 5017.8931) (3535.4656 5020.3206) (3535.8779 5022.9008) (3535.4656 5025.4809)
      (3534.2748 5027.9084) (3532.3817 5030.1069) (3529.9237 5031.9389) (3527.084 5033.3893) (3524.0611 5034.4427)
      (3521.0229 5035.1603) (3518.1832 5035.6031) (3515.6641 5035.9237) (3513.5725 5036.2443) (3511.9389 5036.7176)
      (3510.7786 5037.4962) (3510.0 5038.6565) (3509.5267 5040.2901) (3509.2061 5042.3817) (3508.8855 5044.9008)
      (3508.4427 5047.7405) (3507.7252 5050.7786) (3506.6718 5053.8015) (3505.2214 5056.6412) (3503.3893 5059.0992)
      (3501.1908 5060.9924) (3498.7634 5062.1832) (3496.1832 5062.5954) (3493.6031 5062.1832) (3491.1756 5060.9924)
      (3488.9771 5059.0992) (3487.145 5056.6412) (3485.6947 5053.8015) (3484.6412 5050.7786) (3483.9237 5047.7405)
      (3483.4809 5044.9008) (3483.1603 5042.3817) (3482.8397 5040.2901) (3482.3664 5038.6565) (3481.5878 5037.4962)
      (3480.4275 5036.7176) (3478.7939 5036.2443) (3476.7023 5035.9237) (3474.1832 5035.6031) (3471.3435 5035.1603)
      (3468.3053 5034.4427) (3465.2824 5033.3893) (3462.4427 5031.9389) (3459.9847 5030.1069) (3458.0916 5027.9084)
      (3456.9008 5025.4809)
    ))
    ; P3010 -- see feature_dimensions_mm.csv
    ("06_ORNAMENT" 1 (
      (3529.084 5232.0) (3530.3206 5224.2137) (3533.8931 5217.1908) (3539.4656 5211.6183) (3546.4885 5208.0458)
      (3554.2748 5206.8092) (3562.0611 5208.0458) (3569.084 5211.6183) (3574.6565 5217.1908) (3578.229 5224.2137)
      (3579.4656 5232.0) (3578.229 5239.7863) (3574.6565 5246.8092) (3569.084 5252.3817) (3562.0611 5255.9542)
      (3554.2748 5257.1908) (3546.4885 5255.9542) (3539.4656 5252.3817) (3533.8931 5246.8092) (3530.3206 5239.7863)
    ))
    ; P3011 -- see feature_dimensions_mm.csv
    ("06_ORNAMENT" 1 (
      (3529.084 4798.5344) (3530.3206 4790.7481) (3533.8931 4783.7252) (3539.4656 4778.1527) (3546.4885 4774.5802)
      (3554.2748 4773.3435) (3562.0611 4774.5802) (3569.084 4778.1527) (3574.6565 4783.7252) (3578.229 4790.7481)
      (3579.4656 4798.5344) (3578.229 4806.3206) (3574.6565 4813.3435) (3569.084 4818.916) (3562.0611 4822.4885)
      (3554.2748 4823.7252) (3546.4885 4822.4885) (3539.4656 4818.916) (3533.8931 4813.3435) (3530.3206 4806.3206)
    ))
    ; P3012 -- see feature_dimensions_mm.csv
    ("06_ORNAMENT" 1 (
      (3529.084 4636.5802) (3530.3206 4628.7939) (3533.8931 4621.771) (3539.4656 4616.1985) (3546.4885 4612.626)
      (3554.2748 4611.3893) (3562.0611 4612.626) (3569.084 4616.1985) (3574.6565 4621.771) (3578.229 4628.7939)
      (3579.4656 4636.5802) (3578.229 4644.3664) (3574.6565 4651.3893) (3569.084 4656.9618) (3562.0611 4660.5344)
      (3554.2748 4661.771) (3546.4885 4660.5344) (3539.4656 4656.9618) (3533.8931 4651.3893) (3530.3206 4644.3664)
    ))
    ; P3013 -- see feature_dimensions_mm.csv
    ("06_ORNAMENT" 1 (
      (3529.084 4203.1145) (3530.3206 4195.3282) (3533.8931 4188.3053) (3539.4656 4182.7328) (3546.4885 4179.1603)
      (3554.2748 4177.9237) (3562.0611 4179.1603) (3569.084 4182.7328) (3574.6565 4188.3053) (3578.229 4195.3282)
      (3579.4656 4203.1145) (3578.229 4210.9008) (3574.6565 4217.9237) (3569.084 4223.4962) (3562.0611 4227.0687)
      (3554.2748 4228.3053) (3546.4885 4227.0687) (3539.4656 4223.4962) (3533.8931 4217.9237) (3530.3206 4210.9008)
    ))
    ; P3014 -- see feature_dimensions_mm.csv
    ("06_ORNAMENT" 1 (
      (3529.084 4041.1603) (3530.3206 4033.374) (3533.8931 4026.3511) (3539.4656 4020.7786) (3546.4885 4017.2061)
      (3554.2748 4015.9695) (3562.0611 4017.2061) (3569.084 4020.7786) (3574.6565 4026.3511) (3578.229 4033.374)
      (3579.4656 4041.1603) (3578.229 4048.9466) (3574.6565 4055.9695) (3569.084 4061.542) (3562.0611 4065.1145)
      (3554.2748 4066.3511) (3546.4885 4065.1145) (3539.4656 4061.542) (3533.8931 4055.9695) (3530.3206 4048.9466)
    ))
    ; P3015 -- see feature_dimensions_mm.csv
    ("06_ORNAMENT" 1 (
      (3534.4733 5125.9389) (3536.0 5120.2748) (3540.1374 5116.1221) (3545.8168 5114.6107) (3551.4809 5116.1221)
      (3555.6336 5120.2748) (3557.145 5125.9389) (3555.6336 5131.6183) (3551.4809 5135.7557) (3545.8168 5137.2824)
      (3540.1374 5135.7557) (3536.0 5131.6183)
    ))
    ; P3016 -- see feature_dimensions_mm.csv
    ("06_ORNAMENT" 1 (
      (3534.4733 4904.5954) (3536.0 4898.916) (3540.1374 4894.7786) (3545.8168 4893.2519) (3551.4809 4894.7786)
      (3555.6336 4898.916) (3557.145 4904.5954) (3555.6336 4910.2595) (3551.4809 4914.4122) (3545.8168 4915.9237)
      (3540.1374 4914.4122) (3536.0 4910.2595)
    ))
    ; P3017 -- see feature_dimensions_mm.csv
    ("06_ORNAMENT" 1 (
      (3534.4733 4530.5191) (3536.0 4524.855) (3540.1374 4520.7023) (3545.8168 4519.1908) (3551.4809 4520.7023)
      (3555.6336 4524.855) (3557.145 4530.5191) (3555.6336 4536.1985) (3551.4809 4540.3359) (3545.8168 4541.8626)
      (3540.1374 4540.3359) (3536.0 4536.1985)
    ))
    ; P3018 -- see feature_dimensions_mm.csv
    ("06_ORNAMENT" 1 (
      (3534.4733 4309.1756) (3536.0 4303.4962) (3540.1374 4299.3588) (3545.8168 4297.8321) (3551.4809 4299.3588)
      (3555.6336 4303.4962) (3557.145 4309.1756) (3555.6336 4314.8397) (3551.4809 4318.9924) (3545.8168 4320.5038)
      (3540.1374 4318.9924) (3536.0 4314.8397)
    ))
    ; P3019 -- see feature_dimensions_mm.csv
    ("06_ORNAMENT" 1 (
      (3534.4733 3935.0992) (3536.0 3929.4351) (3540.1374 3925.2824) (3545.8168 3923.771) (3551.4809 3925.2824)
      (3555.6336 3929.4351) (3557.145 3935.0992) (3555.6336 3940.7786) (3551.4809 3944.916) (3545.8168 3946.4427)
      (3540.1374 3944.916) (3536.0 3940.7786)
    ))
    ; P3020 -- see feature_dimensions_mm.csv
    ("06_ORNAMENT" 1 (
      (3591.8168 5211.7557) (3593.3282 5206.0916) (3597.4809 5201.9389) (3603.145 5200.4275) (3608.8092 5201.9389)
      (3612.9618 5206.0916) (3614.4885 5211.7557) (3612.9618 5217.4198) (3608.8092 5221.5725) (3603.145 5223.0992)
      (3597.4809 5221.5725) (3593.3282 5217.4198)
    ))
    ; P3021 -- see feature_dimensions_mm.csv
    ("06_ORNAMENT" 1 (
      (3591.8168 4818.7786) (3593.3282 4813.1145) (3597.4809 4808.9618) (3603.145 4807.4351) (3608.8092 4808.9618)
      (3612.9618 4813.1145) (3614.4885 4818.7786) (3612.9618 4824.4427) (3608.8092 4828.5954) (3603.145 4830.1069)
      (3597.4809 4828.5954) (3593.3282 4824.4427)
    ))
    ; P3022 -- see feature_dimensions_mm.csv
    ("06_ORNAMENT" 1 (
      (3591.8168 4616.3359) (3593.3282 4610.6718) (3597.4809 4606.5191) (3603.145 4605.0076) (3608.8092 4606.5191)
      (3612.9618 4610.6718) (3614.4885 4616.3359) (3612.9618 4622.0) (3608.8092 4626.1527) (3603.145 4627.6794)
      (3597.4809 4626.1527) (3593.3282 4622.0)
    ))
    ; P3023 -- see feature_dimensions_mm.csv
    ("06_ORNAMENT" 1 (
      (3591.8168 4223.3588) (3593.3282 4217.6947) (3597.4809 4213.542) (3603.145 4212.0153) (3608.8092 4213.542)
      (3612.9618 4217.6947) (3614.4885 4223.3588) (3612.9618 4229.0229) (3608.8092 4233.1756) (3603.145 4234.687)
      (3597.4809 4233.1756) (3593.3282 4229.0229)
    ))
    ; P3024 -- see feature_dimensions_mm.csv
    ("06_ORNAMENT" 1 (
      (3591.8168 4020.916) (3593.3282 4015.2519) (3597.4809 4011.0992) (3603.145 4009.5878) (3608.8092 4011.0992)
      (3612.9618 4015.2519) (3614.4885 4020.916) (3612.9618 4026.5802) (3608.8092 4030.7328) (3603.145 4032.2595)
      (3597.4809 4030.7328) (3593.3282 4026.5802)
    ))
    ; P3025 -- see feature_dimensions_mm.csv
    ("06_ORNAMENT" 1 (
      (3606.4275 6098.8092) (3606.8702 6103.8168) (3608.2137 6108.687) (3610.7023 6113.6794) (3614.1221 6118.626)
      (3618.3206 6123.374) (3623.084 6127.7863) (3628.229 6131.6947) (3633.5725 6134.9466) (3638.9313 6137.4046)
      (3645.1145 6139.0229) (3652.6412 6139.9237) (3660.9008 6140.2137) (3669.2824 6139.9847) (3677.145 6139.3282)
      (3683.9084 6138.3664) (3688.9313 6137.1908) (3691.6031 6135.8779) (3691.1908 6134.3206) (3687.9847 6132.3817)
      (3682.8702 6130.1069) (3676.7176 6127.5725) (3670.4275 6124.8397) (3664.8702 6121.9542) (3660.9466 6119.0076)
      (3659.542 6116.0305) (3660.4733 6112.6718) (3662.8092 6108.7328) (3666.3511 6104.4733) (3670.855 6100.1832)
      (3676.0763 6096.1679) (3681.8168 6092.7023) (3685.7099 6090.9924) (3682.4733 6090.1527) (3646.7328 6079.4962)
      (3617.3282 6069.4962) (3615.9389 6070.9008) (3612.0763 6076.3817) (3609.2977 6082.0611) (3607.5267 6087.7863)
      (3606.5954 6093.4198)
    ))
    ; P3026 -- see feature_dimensions_mm.csv
    ("06_ORNAMENT" 1 (
      (3611.9389 5312.9771) (3613.4656 5307.313) (3617.6183 5303.1603) (3623.2824 5301.6336) (3628.9466 5303.1603)
      (3633.0992 5307.313) (3634.626 5312.9771) (3633.0992 5318.6412) (3628.9466 5322.7939) (3623.2824 5324.3053)
      (3617.6183 5322.7939) (3613.4656 5318.6412)
    ))
    ; P3027 -- see feature_dimensions_mm.csv
    ("06_ORNAMENT" 1 (
      (3611.9389 4717.5573) (3613.4656 4711.8931) (3617.6183 4707.7405) (3623.2824 4706.2137) (3628.9466 4707.7405)
      (3633.0992 4711.8931) (3634.626 4717.5573) (3633.0992 4723.2214) (3628.9466 4727.374) (3623.2824 4728.8855)
      (3617.6183 4727.374) (3613.4656 4723.2214)
    ))
    ; P3028 -- see feature_dimensions_mm.csv
    ("06_ORNAMENT" 1 (
      (3611.9389 4122.1374) (3613.4656 4116.4733) (3617.6183 4112.3206) (3623.2824 4110.7939) (3628.9466 4112.3206)
      (3633.0992 4116.4733) (3634.626 4122.1374) (3633.0992 4127.8015) (3628.9466 4131.9542) (3623.2824 4133.4656)
      (3617.6183 4131.9542) (3613.4656 4127.8015)
    ))
    ; P3029 -- see feature_dimensions_mm.csv
    ("06_ORNAMENT" 1 (
      (3641.9847 5275.0687) (3643.2061 5268.9313) (3646.687 5263.7252) (3651.8779 5260.2595) (3658.0153 5259.0382)
      (3664.1527 5260.2595) (3669.3435 5263.7252) (3672.8244 5268.9313) (3674.0458 5275.0687) (3672.8244 5281.2061)
      (3669.3435 5286.3969) (3664.1527 5289.8779) (3658.0153 5291.0992) (3651.8779 5289.8779) (3646.687 5286.3969)
      (3643.2061 5281.2061)
    ))
    ; P3030 -- see feature_dimensions_mm.csv
    ("06_ORNAMENT" 1 (
      (3641.9847 5198.7328) (3643.2061 5192.5954) (3646.687 5187.3893) (3651.8779 5183.9237) (3658.0153 5182.7023)
      (3664.1527 5183.9237) (3669.3435 5187.3893) (3672.8244 5192.5954) (3674.0458 5198.7328) (3672.8244 5204.8702)
      (3669.3435 5210.0611) (3664.1527 5213.542) (3658.0153 5214.7634) (3651.8779 5213.542) (3646.687 5210.0611)
      (3643.2061 5204.8702)
    ))
    ; P3031 -- see feature_dimensions_mm.csv
    ("06_ORNAMENT" 1 (
      (3641.9847 5122.3969) (3643.2061 5116.2595) (3646.687 5111.0534) (3651.8779 5107.5878) (3658.0153 5106.3664)
      (3664.1527 5107.5878) (3669.3435 5111.0534) (3672.8244 5116.2595) (3674.0458 5122.3969) (3672.8244 5128.5344)
      (3669.3435 5133.7252) (3664.1527 5137.2061) (3658.0153 5138.4275) (3651.8779 5137.2061) (3646.687 5133.7252)
      (3643.2061 5128.5344)
    ))
    ; P3032 -- see feature_dimensions_mm.csv
    ("06_ORNAMENT" 1 (
      (3641.9847 5046.0611) (3643.2061 5039.9237) (3646.687 5034.7176) (3651.8779 5031.2519) (3658.0153 5030.0305)
      (3664.1527 5031.2519) (3669.3435 5034.7176) (3672.8244 5039.9237) (3674.0458 5046.0611) (3672.8244 5052.1985)
      (3669.3435 5057.3893) (3664.1527 5060.8702) (3658.0153 5062.0916) (3651.8779 5060.8702) (3646.687 5057.3893)
      (3643.2061 5052.1985)
    ))
    ; P3033 -- see feature_dimensions_mm.csv
    ("06_ORNAMENT" 1 (
      (3641.9847 4969.7252) (3643.2061 4963.5878) (3646.687 4958.3817) (3651.8779 4954.916) (3658.0153 4953.6947)
      (3664.1527 4954.916) (3669.3435 4958.3817) (3672.8244 4963.5878) (3674.0458 4969.7252) (3672.8244 4975.8626)
      (3669.3435 4981.0534) (3664.1527 4984.5344) (3658.0153 4985.7557) (3651.8779 4984.5344) (3646.687 4981.0534)
      (3643.2061 4975.8626)
    ))
    ; P3034 -- see feature_dimensions_mm.csv
    ("06_ORNAMENT" 1 (
      (3641.9847 4893.3893) (3643.2061 4887.2519) (3646.687 4882.0458) (3651.8779 4878.5802) (3658.0153 4877.3588)
      (3664.1527 4878.5802) (3669.3435 4882.0458) (3672.8244 4887.2519) (3674.0458 4893.3893) (3672.8244 4899.5267)
      (3669.3435 4904.7176) (3664.1527 4908.1985) (3658.0153 4909.4198) (3651.8779 4908.1985) (3646.687 4904.7176)
      (3643.2061 4899.5267)
    ))
    ; P3035 -- see feature_dimensions_mm.csv
    ("06_ORNAMENT" 1 (
      (3641.9847 4817.0534) (3643.2061 4810.916) (3646.687 4805.7099) (3651.8779 4802.2443) (3658.0153 4801.0229)
      (3664.1527 4802.2443) (3669.3435 4805.7099) (3672.8244 4810.916) (3674.0458 4817.0534) (3672.8244 4823.1908)
      (3669.3435 4828.3817) (3664.1527 4831.8626) (3658.0153 4833.084) (3651.8779 4831.8626) (3646.687 4828.3817)
      (3643.2061 4823.1908)
    ))
    ; P3036 -- see feature_dimensions_mm.csv
    ("06_ORNAMENT" 1 (
      (3641.9847 4664.3817) (3643.2061 4658.2443) (3646.687 4653.0382) (3651.8779 4649.5725) (3658.0153 4648.3511)
      (3664.1527 4649.5725) (3669.3435 4653.0382) (3672.8244 4658.2443) (3674.0458 4664.3817) (3672.8244 4670.5191)
      (3669.3435 4675.7099) (3664.1527 4679.1908) (3658.0153 4680.4122) (3651.8779 4679.1908) (3646.687 4675.7099)
      (3643.2061 4670.5191)
    ))
    ; P3037 -- see feature_dimensions_mm.csv
    ("06_ORNAMENT" 1 (
      (3641.9847 4588.0458) (3643.2061 4581.9084) (3646.687 4576.7023) (3651.8779 4573.2366) (3658.0153 4572.0153)
      (3664.1527 4573.2366) (3669.3435 4576.7023) (3672.8244 4581.9084) (3674.0458 4588.0458) (3672.8244 4594.1832)
      (3669.3435 4599.374) (3664.1527 4602.855) (3658.0153 4604.0763) (3651.8779 4602.855) (3646.687 4599.374)
      (3643.2061 4594.1832)
    ))
    ; P3038 -- see feature_dimensions_mm.csv
    ("06_ORNAMENT" 1 (
      (3641.9847 4511.7099) (3643.2061 4505.5725) (3646.687 4500.3664) (3651.8779 4496.9008) (3658.0153 4495.6794)
      (3664.1527 4496.9008) (3669.3435 4500.3664) (3672.8244 4505.5725) (3674.0458 4511.7099) (3672.8244 4517.8473)
      (3669.3435 4523.0382) (3664.1527 4526.5191) (3658.0153 4527.7405) (3651.8779 4526.5191) (3646.687 4523.0382)
      (3643.2061 4517.8473)
    ))
    ; P3039 -- see feature_dimensions_mm.csv
    ("06_ORNAMENT" 1 (
      (3641.9847 4359.0382) (3643.2061 4352.9008) (3646.687 4347.6947) (3651.8779 4344.229) (3658.0153 4343.0076)
      (3664.1527 4344.229) (3669.3435 4347.6947) (3672.8244 4352.9008) (3674.0458 4359.0382) (3672.8244 4365.1756)
      (3669.3435 4370.3664) (3664.1527 4373.8473) (3658.0153 4375.0687) (3651.8779 4373.8473) (3646.687 4370.3664)
      (3643.2061 4365.1756)
    ))
    ; P3040 -- see feature_dimensions_mm.csv
    ("06_ORNAMENT" 1 (
      (3641.9847 4282.7023) (3643.2061 4276.5649) (3646.687 4271.3588) (3651.8779 4267.8931) (3658.0153 4266.6718)
      (3664.1527 4267.8931) (3669.3435 4271.3588) (3672.8244 4276.5649) (3674.0458 4282.7023) (3672.8244 4288.8397)
      (3669.3435 4294.0305) (3664.1527 4297.5115) (3658.0153 4298.7328) (3651.8779 4297.5115) (3646.687 4294.0305)
      (3643.2061 4288.8397)
    ))
    ; P3041 -- see feature_dimensions_mm.csv
    ("06_ORNAMENT" 1 (
      (3641.9847 4206.3664) (3643.2061 4200.229) (3646.687 4195.0229) (3651.8779 4191.5573) (3658.0153 4190.3359)
      (3664.1527 4191.5573) (3669.3435 4195.0229) (3672.8244 4200.229) (3674.0458 4206.3664) (3672.8244 4212.5038)
      (3669.3435 4217.6947) (3664.1527 4221.1756) (3658.0153 4222.3969) (3651.8779 4221.1756) (3646.687 4217.6947)
      (3643.2061 4212.5038)
    ))
    ; P3042 -- see feature_dimensions_mm.csv
    ("06_ORNAMENT" 1 (
      (3641.9847 4053.6947) (3643.2061 4047.5573) (3646.687 4042.3511) (3651.8779 4038.8855) (3658.0153 4037.6641)
      (3664.1527 4038.8855) (3669.3435 4042.3511) (3672.8244 4047.5573) (3674.0458 4053.6947) (3672.8244 4059.8321)
      (3669.3435 4065.0229) (3664.1527 4068.5038) (3658.0153 4069.7252) (3651.8779 4068.5038) (3646.687 4065.0229)
      (3643.2061 4059.8321)
    ))
    ; P3043 -- see feature_dimensions_mm.csv
    ("06_ORNAMENT" 1 (
      (3641.9847 3977.3588) (3643.2061 3971.2214) (3646.687 3966.0153) (3651.8779 3962.5496) (3658.0153 3961.3282)
      (3664.1527 3962.5496) (3669.3435 3966.0153) (3672.8244 3971.2214) (3674.0458 3977.3588) (3672.8244 3983.4962)
      (3669.3435 3988.687) (3664.1527 3992.1679) (3658.0153 3993.3893) (3651.8779 3992.1679) (3646.687 3988.687)
      (3643.2061 3983.4962)
    ))
    ; P3044 -- see feature_dimensions_mm.csv
    ("06_ORNAMENT" 1 (
      (3641.9847 3901.0229) (3643.2061 3894.8855) (3646.687 3889.6794) (3651.8779 3886.2137) (3658.0153 3884.9924)
      (3664.1527 3886.2137) (3669.3435 3889.6794) (3672.8244 3894.8855) (3674.0458 3901.0229) (3672.8244 3907.1603)
      (3669.3435 3912.3511) (3664.1527 3915.8321) (3658.0153 3917.0534) (3651.8779 3915.8321) (3646.687 3912.3511)
      (3643.2061 3907.1603)
    ))
    ; P3045 -- see feature_dimensions_mm.csv
    ("06_ORNAMENT" 1 (
      (3670.229 7374.0458) (3671.5878 7371.5267) (3675.2977 7369.4809) (3680.3359 7368.1527) (3685.3893 7367.4656)
      (3689.1756 7367.0076) (3690.855 7366.1527) (3690.2595 7364.3511) (3687.9237 7361.3435) (3684.8397 7357.2824)
      (3682.2137 7352.7786) (3681.0382 7348.7176) (3681.8626 7345.9847) (3684.5954 7345.1603) (3688.6565 7346.3359)
      (3693.1603 7348.9618) (3697.2214 7352.0458) (3700.229 7354.3817) (3702.0305 7354.9771) (3702.8855 7353.2977)
      (3703.3435 7349.5115) (3704.0458 7344.458) (3705.3588 7339.4198) (3707.4046 7335.7099) (3709.9237 7334.3511)
      (3712.4427 7335.7099) (3714.4885 7339.4198) (3715.8168 7344.458) (3716.5038 7349.5115) (3716.9618 7353.2977)
      (3717.8168 7354.9771) (3719.6183 7354.3817) (3722.626 7352.0458) (3726.687 7348.9618) (3731.1908 7346.3359)
      (3735.2519 7345.1603) (3737.9847 7345.9847) (3738.8092 7348.7176) (3737.6336 7352.7786) (3735.0076 7357.2824)
      (3731.9237 7361.3435) (3729.5878 7364.3511) (3728.9924 7366.1527) (3730.6718 7367.0076) (3734.458 7367.4656)
      (3739.5115 7368.1527) (3744.5496 7369.4809) (3748.2595 7371.5267) (3749.6183 7374.0458) (3748.2595 7376.5649)
      (3744.5496 7378.6107) (3739.5115 7379.9237) (3734.458 7380.626) (3730.6718 7381.084) (3728.9924 7381.9389)
      (3729.5878 7383.7405) (3731.9237 7386.7481) (3735.0076 7390.8092) (3737.6336 7395.313) (3738.8092 7399.374)
      (3737.9847 7402.1069) (3735.2519 7402.9313) (3731.1908 7401.7557) (3726.687 7399.1298) (3722.626 7396.0458)
      (3719.6183 7393.7099) (3717.8168 7393.1145) (3716.9618 7394.7939) (3716.5038 7398.5802) (3715.8168 7403.6336)
      (3714.4885 7408.6718) (3712.4427 7412.3817) (3709.9237 7413.7405) (3707.4046 7412.3817) (3705.3588 7408.6718)
      (3704.0458 7403.6336) (3703.3435 7398.5802) (3702.8855 7394.7939) (3702.0305 7393.1145) (3700.229 7393.7099)
      (3697.2214 7396.0458) (3693.1603 7399.1298) (3688.6565 7401.7557) (3684.5954 7402.9313) (3681.8626 7402.1069)
      (3681.0382 7399.374) (3682.2137 7395.313) (3684.8397 7390.8092) (3687.9237 7386.7481) (3690.2595 7383.7405)
      (3690.855 7381.9389) (3689.1756 7381.084) (3685.3893 7380.626) (3680.3359 7379.9237) (3675.2977 7378.6107)
      (3671.5878 7376.5649)
    ))
    ; P3046 -- see feature_dimensions_mm.csv
    ("06_ORNAMENT" 1 (
      (3670.229 7206.1069) (3671.5878 7203.5878) (3675.2977 7201.542) (3680.3359 7200.2137) (3685.3893 7199.5267)
      (3689.1756 7199.0687) (3690.855 7198.2137) (3690.2595 7196.4122) (3687.9237 7193.4046) (3684.8397 7189.3435)
      (3682.2137 7184.8397) (3681.0382 7180.7786) (3681.8626 7178.0458) (3684.5954 7177.2214) (3688.6565 7178.3969)
      (3693.1603 7181.0229) (3697.2214 7184.1069) (3700.229 7186.4427) (3702.0305 7187.0382) (3702.8855 7185.3588)
      (3703.3435 7181.5725) (3704.0458 7176.5191) (3705.3588 7171.4809) (3707.4046 7167.771) (3709.9237 7166.4122)
      (3712.4427 7167.771) (3714.4885 7171.4809) (3715.8168 7176.5191) (3716.5038 7181.5725) (3716.9618 7185.3588)
      (3717.8168 7187.0382) (3719.6183 7186.4427) (3722.626 7184.1069) (3726.687 7181.0229) (3731.1908 7178.3969)
      (3735.2519 7177.2214) (3737.9847 7178.0458) (3738.8092 7180.7786) (3737.6336 7184.8397) (3735.0076 7189.3435)
      (3731.9237 7193.4046) (3729.5878 7196.4122) (3728.9924 7198.2137) (3730.6718 7199.0687) (3734.458 7199.5267)
      (3739.5115 7200.2137) (3744.5496 7201.542) (3748.2595 7203.5878) (3749.6183 7206.1069) (3748.2595 7208.626)
      (3744.5496 7210.6718) (3739.5115 7211.9847) (3734.458 7212.687) (3730.6718 7213.145) (3728.9924 7214.0)
      (3729.5878 7215.8015) (3731.9237 7218.8092) (3735.0076 7222.8702) (3737.6336 7227.374) (3738.8092 7231.4351)
      (3737.9847 7234.1679) (3735.2519 7234.9924) (3731.1908 7233.8168) (3726.687 7231.1908) (3722.626 7228.1069)
      (3719.6183 7225.771) (3717.8168 7225.1756) (3716.9618 7226.855) (3716.5038 7230.6412) (3715.8168 7235.6947)
      (3714.4885 7240.7328) (3712.4427 7244.4427) (3709.9237 7245.8015) (3707.4046 7244.4427) (3705.3588 7240.7328)
      (3704.0458 7235.6947) (3703.3435 7230.6412) (3702.8855 7226.855) (3702.0305 7225.1756) (3700.229 7225.771)
      (3697.2214 7228.1069) (3693.1603 7231.1908) (3688.6565 7233.8168) (3684.5954 7234.9924) (3681.8626 7234.1679)
      (3681.0382 7231.4351) (3682.2137 7227.374) (3684.8397 7222.8702) (3687.9237 7218.8092) (3690.2595 7215.8015)
      (3690.855 7214.0) (3689.1756 7213.145) (3685.3893 7212.687) (3680.3359 7211.9847) (3675.2977 7210.6718)
      (3671.5878 7208.626)
    ))
    ; P3047 -- see feature_dimensions_mm.csv
    ("06_ORNAMENT" 1 (
      (3673.8931 3007.6336) (3674.6107 3006.3206) (3676.5344 3005.2519) (3679.1756 3004.5496) (3681.8168 3004.1985)
      (3683.8015 3003.9542) (3684.687 3003.4962) (3684.3817 3002.5649) (3683.145 3000.9924) (3681.542 2998.8702)
      (3680.1679 2996.5038) (3679.542 2994.3817) (3679.9695 2992.9466) (3681.4046 2992.5191) (3683.5267 2993.145)
      (3685.8931 2994.5191) (3688.0153 2996.1221) (3689.5878 2997.3588) (3690.5191 2997.6641) (3690.9771 2996.7786)
      (3691.2214 2994.7939) (3691.5725 2992.1527) (3692.2748 2989.5115) (3693.3435 2987.5878) (3694.6565 2986.8702)
      (3695.9695 2987.5878) (3697.0382 2989.5115) (3697.7405 2992.1527) (3698.0916 2994.7939) (3698.3359 2996.7786)
      (3698.7939 2997.6641) (3699.7252 2997.3588) (3701.2977 2996.1221) (3703.4198 2994.5191) (3705.7863 2993.145)
      (3707.9084 2992.5191) (3709.3435 2992.9466) (3709.771 2994.3817) (3709.145 2996.5038) (3707.771 2998.8702)
      (3706.1679 3000.9924) (3704.9313 3002.5649) (3704.626 3003.4962) (3705.5115 3003.9542) (3707.4962 3004.1985)
      (3710.1374 3004.5496) (3712.7786 3005.2519) (3714.7023 3006.3206) (3715.4198 3007.6336) (3714.7023 3008.9466)
      (3712.7786 3010.0153) (3710.1374 3010.7176) (3707.4962 3011.0687) (3705.5115 3011.313) (3704.626 3011.771)
      (3704.9313 3012.7023) (3706.1679 3014.2748) (3707.771 3016.3969) (3709.145 3018.7634) (3709.771 3020.8855)
      (3709.3435 3022.3206) (3707.9084 3022.7481) (3705.7863 3022.1221) (3703.4198 3020.7481) (3701.2977 3019.145)
      (3699.7252 3017.9084) (3698.7939 3017.6031) (3698.3359 3018.4885) (3698.0916 3020.4733) (3697.7405 3023.1145)
      (3697.0382 3025.7557) (3695.9695 3027.6794) (3694.6565 3028.3969) (3693.3435 3027.6794) (3692.2748 3025.7557)
      (3691.5725 3023.1145) (3691.2214 3020.4733) (3690.9771 3018.4885) (3690.5191 3017.6031) (3689.5878 3017.9084)
      (3688.0153 3019.145) (3685.8931 3020.7481) (3683.5267 3022.1221) (3681.4046 3022.7481) (3679.9695 3022.3206)
      (3679.542 3020.8855) (3680.1679 3018.7634) (3681.542 3016.3969) (3683.145 3014.2748) (3684.3817 3012.7023)
      (3684.687 3011.771) (3683.8015 3011.313) (3681.8168 3011.0687) (3679.1756 3010.7176) (3676.5344 3010.0153)
      (3674.6107 3008.9466)
    ))
    ; P3048 -- see feature_dimensions_mm.csv
    ("06_ORNAMENT" 1 (
      (3673.8931 2900.7634) (3674.6107 2899.4504) (3676.5344 2898.3817) (3679.1756 2897.6794) (3681.8168 2897.3282)
      (3683.8015 2897.084) (3684.687 2896.626) (3684.3817 2895.6947) (3683.145 2894.1221) (3681.542 2892.0)
      (3680.1679 2889.6336) (3679.542 2887.5115) (3679.9695 2886.0763) (3681.4046 2885.6489) (3683.5267 2886.2748)
      (3685.8931 2887.6489) (3688.0153 2889.2519) (3689.5878 2890.4885) (3690.5191 2890.7939) (3690.9771 2889.9084)
      (3691.2214 2887.9237) (3691.5725 2885.2824) (3692.2748 2882.6412) (3693.3435 2880.7176) (3694.6565 2880.0)
      (3695.9695 2880.7176) (3697.0382 2882.6412) (3697.7405 2885.2824) (3698.0916 2887.9237) (3698.3359 2889.9084)
      (3698.7939 2890.7939) (3699.7252 2890.4885) (3701.2977 2889.2519) (3703.4198 2887.6489) (3705.7863 2886.2748)
      (3707.9084 2885.6489) (3709.3435 2886.0763) (3709.771 2887.5115) (3709.145 2889.6336) (3707.771 2892.0)
      (3706.1679 2894.1221) (3704.9313 2895.6947) (3704.626 2896.626) (3705.5115 2897.084) (3707.4962 2897.3282)
      (3710.1374 2897.6794) (3712.7786 2898.3817) (3714.7023 2899.4504) (3715.4198 2900.7634) (3714.7023 2902.0763)
      (3712.7786 2903.145) (3710.1374 2903.8473) (3707.4962 2904.1985) (3705.5115 2904.4427) (3704.626 2904.9008)
      (3704.9313 2905.8321) (3706.1679 2907.4046) (3707.771 2909.5267) (3709.145 2911.8931) (3709.771 2914.0153)
      (3709.3435 2915.4504) (3707.9084 2915.8779) (3705.7863 2915.2519) (3703.4198 2913.8779) (3701.2977 2912.2748)
      (3699.7252 2911.0382) (3698.7939 2910.7328) (3698.3359 2911.6183) (3698.0916 2913.6031) (3697.7405 2916.2443)
      (3697.0382 2918.8855) (3695.9695 2920.8092) (3694.6565 2921.5267) (3693.3435 2920.8092) (3692.2748 2918.8855)
      (3691.5725 2916.2443) (3691.2214 2913.6031) (3690.9771 2911.6183) (3690.5191 2910.7328) (3689.5878 2911.0382)
      (3688.0153 2912.2748) (3685.8931 2913.8779) (3683.5267 2915.2519) (3681.4046 2915.8779) (3679.9695 2915.4504)
      (3679.542 2914.0153) (3680.1679 2911.8931) (3681.542 2909.5267) (3683.145 2907.4046) (3684.3817 2905.8321)
      (3684.687 2904.9008) (3683.8015 2904.4427) (3681.8168 2904.1985) (3679.1756 2903.8473) (3676.5344 2903.145)
      (3674.6107 2902.0763)
    ))
    ; P3049 -- see feature_dimensions_mm.csv
    ("06_ORNAMENT" 1 (
      (3688.5496 3007.6336) (3689.0076 3005.2977) (3690.3359 3003.313) (3692.3206 3001.9847) (3694.6565 3001.5267)
      (3696.9924 3001.9847) (3698.9771 3003.313) (3700.3053 3005.2977) (3700.7634 3007.6336) (3700.3053 3009.9695)
      (3698.9771 3011.9542) (3696.9924 3013.2824) (3694.6565 3013.7405) (3692.3206 3013.2824) (3690.3359 3011.9542)
      (3689.0076 3009.9695)
    ))
    ; P3050 -- see feature_dimensions_mm.csv
    ("06_ORNAMENT" 1 (
      (3688.5496 2900.7634) (3689.0076 2898.4275) (3690.3359 2896.4427) (3692.3206 2895.1145) (3694.6565 2894.6565)
      (3696.9924 2895.1145) (3698.9771 2896.4427) (3700.3053 2898.4275) (3700.7634 2900.7634) (3700.3053 2903.0992)
      (3698.9771 2905.084) (3696.9924 2906.4122) (3694.6565 2906.8702) (3692.3206 2906.4122) (3690.3359 2905.084)
      (3689.0076 2903.0992)
    ))
    ; P3051 -- see feature_dimensions_mm.csv
    ("06_ORNAMENT" 1 (
      (3694.6565 5816.7939) (3722.3969 5815.4046) (3751.5878 5816.7481) (3781.8473 5820.5802) (3812.7939 5826.626)
      (3844.0458 5834.6565) (3875.2214 5844.3969) (3905.9542 5855.6183) (3935.8473 5868.0611) (3964.5191 5881.4656)
      (3991.6031 5895.5878) (4016.7023 5910.1832) (4039.4351 5924.9771) (4059.4504 5939.7405) (4076.3359 5954.1985)
      (4051.8779 5953.7863) (4025.2824 5951.7557) (3996.9466 5948.1679) (3967.3435 5943.0687) (3936.8702 5936.4733)
      (3905.9695 5928.4275) (3875.0534 5918.9771) (3844.5802 5908.1679) (3814.9466 5896.0305) (3786.6107 5882.5954)
      (3759.9847 5867.9237) (3735.4962 5852.0305) (3713.5725 5834.9771)
    ))
    ; P3052 -- see feature_dimensions_mm.csv
    ("06_ORNAMENT" 1 (
      (3700.7939 7374.0458) (3701.4962 7370.5496) (3703.4656 7367.5878) (3706.4275 7365.6183) (3709.9237 7364.916)
      (3713.4198 7365.6183) (3716.3817 7367.5878) (3718.3511 7370.5496) (3719.0534 7374.0458) (3718.3511 7377.542)
      (3716.3817 7380.5038) (3713.4198 7382.4733) (3709.9237 7383.1756) (3706.4275 7382.4733) (3703.4656 7380.5038)
      (3701.4962 7377.542)
    ))
    ; P3053 -- see feature_dimensions_mm.csv
    ("06_ORNAMENT" 1 (
      (3700.7939 7206.1069) (3701.4962 7202.6107) (3703.4656 7199.6489) (3706.4275 7197.6794) (3709.9237 7196.9771)
      (3713.4198 7197.6794) (3716.3817 7199.6489) (3718.3511 7202.6107) (3719.0534 7206.1069) (3718.3511 7209.6031)
      (3716.3817 7212.5649) (3713.4198 7214.5344) (3709.9237 7215.2366) (3706.4275 7214.5344) (3703.4656 7212.5649)
      (3701.4962 7209.6031)
    ))
    ; P3054 -- see feature_dimensions_mm.csv
    ("06_ORNAMENT" 1 (
      (3963.9695 3007.6336) (3964.687 3006.3206) (3966.6107 3005.2519) (3969.2519 3004.5496) (3971.8931 3004.1985)
      (3973.8779 3003.9542) (3974.7634 3003.4962) (3974.458 3002.5649) (3973.2214 3000.9924) (3971.6183 2998.8702)
      (3970.2443 2996.5038) (3969.6183 2994.3817) (3970.0458 2992.9466) (3971.4809 2992.5191) (3973.6031 2993.145)
      (3975.9695 2994.5191) (3978.0916 2996.1221) (3979.6641 2997.3588) (3980.5954 2997.6641) (3981.0534 2996.7786)
      (3981.2977 2994.7939) (3981.6489 2992.1527) (3982.3511 2989.5115) (3983.4198 2987.5878) (3984.7328 2986.8702)
      (3986.0458 2987.5878) (3987.1145 2989.5115) (3987.8168 2992.1527) (3988.1679 2994.7939) (3988.4122 2996.7786)
      (3988.8702 2997.6641) (3989.8015 2997.3588) (3991.374 2996.1221) (3993.4962 2994.5191) (3995.8626 2993.145)
      (3997.9847 2992.5191) (3999.4198 2992.9466) (3999.8473 2994.3817) (3999.2214 2996.5038) (3997.8473 2998.8702)
      (3996.2443 3000.9924) (3995.0076 3002.5649) (3994.7023 3003.4962) (3995.5878 3003.9542) (3997.5725 3004.1985)
      (4000.2137 3004.5496) (4002.855 3005.2519) (4004.7786 3006.3206) (4005.4962 3007.6336) (4004.7786 3008.9466)
      (4002.855 3010.0153) (4000.2137 3010.7176) (3997.5725 3011.0687) (3995.5878 3011.313) (3994.7023 3011.771)
      (3995.0076 3012.7023) (3996.2443 3014.2748) (3997.8473 3016.3969) (3999.2214 3018.7634) (3999.8473 3020.8855)
      (3999.4198 3022.3206) (3997.9847 3022.7481) (3995.8626 3022.1221) (3993.4962 3020.7481) (3991.374 3019.145)
      (3989.8015 3017.9084) (3988.8702 3017.6031) (3988.4122 3018.4885) (3988.1679 3020.4733) (3987.8168 3023.1145)
      (3987.1145 3025.7557) (3986.0458 3027.6794) (3984.7328 3028.3969) (3983.4198 3027.6794) (3982.3511 3025.7557)
      (3981.6489 3023.1145) (3981.2977 3020.4733) (3981.0534 3018.4885) (3980.5954 3017.6031) (3979.6641 3017.9084)
      (3978.0916 3019.145) (3975.9695 3020.7481) (3973.6031 3022.1221) (3971.4809 3022.7481) (3970.0458 3022.3206)
      (3969.6183 3020.8855) (3970.2443 3018.7634) (3971.6183 3016.3969) (3973.2214 3014.2748) (3974.458 3012.7023)
      (3974.7634 3011.771) (3973.8779 3011.313) (3971.8931 3011.0687) (3969.2519 3010.7176) (3966.6107 3010.0153)
      (3964.687 3008.9466)
    ))
    ; P3055 -- see feature_dimensions_mm.csv
    ("06_ORNAMENT" 1 (
      (3963.9695 2900.7634) (3964.687 2899.4504) (3966.6107 2898.3817) (3969.2519 2897.6794) (3971.8931 2897.3282)
      (3973.8779 2897.084) (3974.7634 2896.626) (3974.458 2895.6947) (3973.2214 2894.1221) (3971.6183 2892.0)
      (3970.2443 2889.6336) (3969.6183 2887.5115) (3970.0458 2886.0763) (3971.4809 2885.6489) (3973.6031 2886.2748)
      (3975.9695 2887.6489) (3978.0916 2889.2519) (3979.6641 2890.4885) (3980.5954 2890.7939) (3981.0534 2889.9084)
      (3981.2977 2887.9237) (3981.6489 2885.2824) (3982.3511 2882.6412) (3983.4198 2880.7176) (3984.7328 2880.0)
      (3986.0458 2880.7176) (3987.1145 2882.6412) (3987.8168 2885.2824) (3988.1679 2887.9237) (3988.4122 2889.9084)
      (3988.8702 2890.7939) (3989.8015 2890.4885) (3991.374 2889.2519) (3993.4962 2887.6489) (3995.8626 2886.2748)
      (3997.9847 2885.6489) (3999.4198 2886.0763) (3999.8473 2887.5115) (3999.2214 2889.6336) (3997.8473 2892.0)
      (3996.2443 2894.1221) (3995.0076 2895.6947) (3994.7023 2896.626) (3995.5878 2897.084) (3997.5725 2897.3282)
      (4000.2137 2897.6794) (4002.855 2898.3817) (4004.7786 2899.4504) (4005.4962 2900.7634) (4004.7786 2902.0763)
      (4002.855 2903.145) (4000.2137 2903.8473) (3997.5725 2904.1985) (3995.5878 2904.4427) (3994.7023 2904.9008)
      (3995.0076 2905.8321) (3996.2443 2907.4046) (3997.8473 2909.5267) (3999.2214 2911.8931) (3999.8473 2914.0153)
      (3999.4198 2915.4504) (3997.9847 2915.8779) (3995.8626 2915.2519) (3993.4962 2913.8779) (3991.374 2912.2748)
      (3989.8015 2911.0382) (3988.8702 2910.7328) (3988.4122 2911.6183) (3988.1679 2913.6031) (3987.8168 2916.2443)
      (3987.1145 2918.8855) (3986.0458 2920.8092) (3984.7328 2921.5267) (3983.4198 2920.8092) (3982.3511 2918.8855)
      (3981.6489 2916.2443) (3981.2977 2913.6031) (3981.0534 2911.6183) (3980.5954 2910.7328) (3979.6641 2911.0382)
      (3978.0916 2912.2748) (3975.9695 2913.8779) (3973.6031 2915.2519) (3971.4809 2915.8779) (3970.0458 2915.4504)
      (3969.6183 2914.0153) (3970.2443 2911.8931) (3971.6183 2909.5267) (3973.2214 2907.4046) (3974.458 2905.8321)
      (3974.7634 2904.9008) (3973.8779 2904.4427) (3971.8931 2904.1985) (3969.2519 2903.8473) (3966.6107 2903.145)
      (3964.687 2902.0763)
    ))
    ; P3056 -- see feature_dimensions_mm.csv
    ("06_ORNAMENT" 1 (
      (3978.626 3007.6336) (3979.084 3005.2977) (3980.4122 3003.313) (3982.3969 3001.9847) (3984.7328 3001.5267)
      (3987.0687 3001.9847) (3989.0534 3003.313) (3990.3817 3005.2977) (3990.8397 3007.6336) (3990.3817 3009.9695)
      (3989.0534 3011.9542) (3987.0687 3013.2824) (3984.7328 3013.7405) (3982.3969 3013.2824) (3980.4122 3011.9542)
      (3979.084 3009.9695)
    ))
    ; P3057 -- see feature_dimensions_mm.csv
    ("06_ORNAMENT" 1 (
      (3978.626 2900.7634) (3979.084 2898.4275) (3980.4122 2896.4427) (3982.3969 2895.1145) (3984.7328 2894.6565)
      (3987.0687 2895.1145) (3989.0534 2896.4427) (3990.3817 2898.4275) (3990.8397 2900.7634) (3990.3817 2903.0992)
      (3989.0534 2905.084) (3987.0687 2906.4122) (3984.7328 2906.8702) (3982.3969 2906.4122) (3980.4122 2905.084)
      (3979.084 2903.0992)
    ))
    ; P3058 -- see feature_dimensions_mm.csv
    ("06_ORNAMENT" 1 (
      (4015.2672 5603.0534) (4041.4656 5607.6489) (4068.3053 5615.1908) (4095.5267 5625.3435) (4098.7786 5626.8244)
      (4099.9695 5620.8092) (4106.8702 5606.1069) (4118.916 5596.229) (4136.5344 5589.8779) (4157.6794 5586.5038)
      (4180.2748 5585.4962) (4202.2748 5586.3053) (4221.6489 5588.3511) (4236.3359 5591.084) (4244.2748 5593.8931)
      (4244.6565 5597.3435) (4239.0687 5602.1985) (4229.0992 5608.2443) (4216.3359 5615.2672) (4202.3664 5623.0534)
      (4188.7939 5631.3893) (4177.1908 5640.0611) (4169.1603 5648.855) (4164.0 5658.1985) (4163.2061 5660.229)
      (4176.458 5668.2137) (4202.229 5685.5725) (4225.9389 5703.2214) (4227.6641 5702.9313) (4233.9237 5703.6031)
      (4240.7634 5705.6641) (4247.8321 5708.9618) (4254.7939 5713.3435) (4261.3282 5718.626) (4267.084 5724.6718)
      (4271.7557 5731.2977) (4275.7557 5739.0382) (4279.5878 5748.2595) (4280.4275 5750.7939) (4291.5115 5761.7252)
      (4308.9466 5780.8092) (4323.8168 5799.2824) (4335.8779 5816.7939) (4313.2061 5811.1603) (4288.9313 5803.5267)
      (4288.3359 5803.2977) (4288.3206 5803.4962) (4286.4122 5813.7405) (4282.687 5823.8015) (4277.2519 5834.2748)
      (4270.4427 5844.8397) (4262.5954 5855.145) (4254.0611 5864.8702) (4245.1908 5873.6336) (4236.3206 5881.145)
      (4227.7863 5887.0229) (4219.145 5891.7863) (4209.8931 5895.9847) (4200.2443 5899.3282) (4190.458 5901.5267)
      (4180.7481 5902.2901) (4171.3588 5901.3282) (4162.5344 5898.3817) (4154.5038 5893.1298) (4146.9924 5885.4046)
      (4139.6794 5875.374) (4132.6718 5863.3588) (4126.1069 5849.6183) (4120.1221 5834.4427) (4114.8244 5818.1221)
      (4110.3664 5800.9466) (4106.8702 5783.2061) (4103.6489 5763.1603) (4100.3053 5739.7863) (4097.3435 5714.4733)
      (4095.8626 5695.6031) (4084.1985 5685.9847) (4063.1145 5666.1832) (4044.3511 5645.6641) (4028.2748 5624.5802)
    ))
    ; P3059 -- see feature_dimensions_mm.csv
    ("06_ORNAMENT" 1 (
      (4079.4504 6014.687) (4080.8244 5996.2595) (4084.7023 5980.626) (4091.6031 5968.855) (4103.6489 5960.9466)
      (4121.2672 5955.8779) (4142.4122 5953.1603) (4165.0076 5952.3664) (4187.0076 5953.0076) (4206.3817 5954.6565)
      (4221.0687 5956.8244) (4229.0076 5959.084) (4229.3893 5961.8473) (4223.8015 5965.7252) (4213.8321 5970.5649)
      (4201.0687 5976.1832) (4187.0992 5982.4122) (4173.5267 5989.084) (4161.9237 5996.0153) (4153.8931 6003.0534)
      (4148.7328 6010.5344) (4144.6565 6018.7786) (4141.5573 6027.5573) (4139.3588 6036.6412) (4137.9237 6045.8015)
      (4137.1908 6054.8092) (4137.0534 6063.4351) (4137.4046 6071.4504) (4138.4885 6079.2519) (4140.4733 6087.2366)
      (4143.2061 6095.145) (4146.5649 6102.7481) (4150.3817 6109.8015) (4154.4885 6116.0458) (4158.7634 6121.2672)
      (4163.0534 6125.1908) (4168.0 6127.771) (4174.0153 6129.2214) (4180.626 6129.6794) (4187.3282 6129.313)
      (4193.6336 6128.2748) (4199.0382 6126.7328) (4203.0534 6124.8397) (4205.1908 6122.7481) (4204.8702 6120.2595)
      (4202.3053 6117.1603) (4198.1985 6113.5267) (4193.2824 6109.4656) (4188.2443 6105.084) (4183.8015 6100.4733)
      (4180.6718 6095.7405) (4179.542 6090.9924) (4180.2901 6085.6336) (4182.1679 6079.313) (4184.9924 6072.5038)
      (4188.5954 6065.6489) (4192.7786 6059.2214) (4197.3588 6053.6641) (4202.1679 6049.4504) (4207.0229 6047.0229)
      (4212.3969 6046.3206) (4218.6565 6046.855) (4225.4962 6048.5038) (4232.5649 6051.145) (4239.5267 6054.6412)
      (4246.0611 6058.8702) (4251.8168 6063.7099) (4256.4885 6069.0076) (4260.4885 6075.1908) (4264.3206 6082.5802)
      (4267.7557 6090.8397) (4270.5802 6099.6947) (4272.5496 6108.8397) (4273.4504 6117.9542) (4273.0534 6126.7634)
      (4271.145 6134.9618) (4267.4198 6143.0076) (4261.9847 6151.3893) (4255.1756 6159.8473) (4247.3282 6168.0916)
      (4238.7939 6175.8626) (4229.9237 6182.8855) (4221.0534 6188.8855) (4212.5191 6193.5878) (4203.8779 6197.4046)
      (4194.626 6200.7634) (4184.9771 6203.4351) (4175.1908 6205.1908) (4165.4809 6205.8015) (4156.0916 6205.0382)
      (4147.2672 6202.6718) (4139.2366 6198.4733) (4131.7252 6192.2901) (4124.4122 6184.2748) (4117.4046 6174.6565)
      (4110.8397 6163.6641) (4104.855 6151.5267) (4099.5573 6138.4733) (4095.0992 6124.7328) (4091.6031 6110.5344)
      (4088.3817 6094.4885) (4085.0382 6075.8015) (4082.0763 6055.542) (4080.0458 6034.8092)
    ))
    ; P3060 -- see feature_dimensions_mm.csv
    ("06_ORNAMENT" 1 (
      (4125.5115 4091.5573) (4125.9542 4101.0687) (4127.2977 4110.3359) (4129.7863 4119.8168) (4133.2061 4129.2061)
      (4137.4046 4138.229) (4142.1679 4146.6107) (4147.313 4154.0305) (4152.6565 4160.2137) (4158.0153 4164.8855)
      (4164.1985 4167.9542) (4171.7252 4169.6641) (4179.9847 4170.2137) (4188.3664 4169.7863) (4196.229 4168.5496)
      (4202.9924 4166.7176) (4208.0153 4164.4733) (4210.687 4161.9847) (4210.2748 4159.0382) (4207.0687 4155.3435)
      (4201.9542 4151.0229) (4195.8015 4146.2137) (4189.5115 4141.0076) (4183.9542 4135.542) (4180.0305 4129.9237)
      (4178.626 4124.2748) (4179.5573 4117.9084) (4181.8931 4110.4122) (4185.4351 4102.3206) (4189.9389 4094.1832)
      (4195.1603 4086.5496) (4200.9008 4079.9542) (4206.916 4074.9466) (4211.3435 4072.8397) (4207.8779 4058.1374)
      (4204.9924 4040.0) (4204.1527 4022.3969) (4205.4351 4011.8321) (4200.1069 4002.7786) (4194.6412 3992.5496)
      (4188.0763 3995.3435) (4171.1145 4003.2519) (4156.6107 4011.4962) (4146.5649 4019.8473) (4140.1221 4028.7328)
      (4135.0229 4038.5191) (4131.1603 4048.9466) (4128.3817 4059.7252) (4126.6107 4070.6107) (4125.6794 4081.313)
    ))
    ; P3061 -- see feature_dimensions_mm.csv
    ("06_ORNAMENT" 1 (
      (4143.5115 7374.0458) (4144.8702 7371.5267) (4148.5802 7369.4809) (4153.6183 7368.1527) (4158.6718 7367.4656)
      (4162.458 7367.0076) (4164.1374 7366.1527) (4163.542 7364.3511) (4161.2061 7361.3435) (4158.1221 7357.2824)
      (4155.4962 7352.7786) (4154.3206 7348.7176) (4155.145 7345.9847) (4157.8779 7345.1603) (4161.9389 7346.3359)
      (4166.4427 7348.9618) (4170.5038 7352.0458) (4173.5115 7354.3817) (4175.313 7354.9771) (4176.1679 7353.2977)
      (4176.626 7349.5115) (4177.3282 7344.458) (4178.6412 7339.4198) (4180.687 7335.7099) (4183.2061 7334.3511)
      (4185.7252 7335.7099) (4187.771 7339.4198) (4189.0992 7344.458) (4189.7863 7349.5115) (4190.2443 7353.2977)
      (4191.0992 7354.9771) (4192.9008 7354.3817) (4195.9084 7352.0458) (4199.9695 7348.9618) (4204.4733 7346.3359)
      (4208.5344 7345.1603) (4211.2672 7345.9847) (4212.0916 7348.7176) (4210.916 7352.7786) (4208.2901 7357.2824)
      (4205.2061 7361.3435) (4202.8702 7364.3511) (4202.2748 7366.1527) (4203.9542 7367.0076) (4207.7405 7367.4656)
      (4212.7939 7368.1527) (4217.8321 7369.4809) (4221.542 7371.5267) (4222.9008 7374.0458) (4221.542 7376.5649)
      (4217.8321 7378.6107) (4212.7939 7379.9237) (4207.7405 7380.626) (4203.9542 7381.084) (4202.2748 7381.9389)
      (4202.8702 7383.7405) (4205.2061 7386.7481) (4208.2901 7390.8092) (4210.916 7395.313) (4212.0916 7399.374)
      (4211.2672 7402.1069) (4208.5344 7402.9313) (4204.4733 7401.7557) (4199.9695 7399.1298) (4195.9084 7396.0458)
      (4192.9008 7393.7099) (4191.0992 7393.1145) (4190.2443 7394.7939) (4189.7863 7398.5802) (4189.0992 7403.6336)
      (4187.771 7408.6718) (4185.7252 7412.3817) (4183.2061 7413.7405) (4180.687 7412.3817) (4178.6412 7408.6718)
      (4177.3282 7403.6336) (4176.626 7398.5802) (4176.1679 7394.7939) (4175.313 7393.1145) (4173.5115 7393.7099)
      (4170.5038 7396.0458) (4166.4427 7399.1298) (4161.9389 7401.7557) (4157.8779 7402.9313) (4155.145 7402.1069)
      (4154.3206 7399.374) (4155.4962 7395.313) (4158.1221 7390.8092) (4161.2061 7386.7481) (4163.542 7383.7405)
      (4164.1374 7381.9389) (4162.458 7381.084) (4158.6718 7380.626) (4153.6183 7379.9237) (4148.5802 7378.6107)
      (4144.8702 7376.5649)
    ))
    ; P3062 -- see feature_dimensions_mm.csv
    ("06_ORNAMENT" 1 (
      (4143.5115 7206.1069) (4144.8702 7203.5878) (4148.5802 7201.542) (4153.6183 7200.2137) (4158.6718 7199.5267)
      (4162.458 7199.0687) (4164.1374 7198.2137) (4163.542 7196.4122) (4161.2061 7193.4046) (4158.1221 7189.3435)
      (4155.4962 7184.8397) (4154.3206 7180.7786) (4155.145 7178.0458) (4157.8779 7177.2214) (4161.9389 7178.3969)
      (4166.4427 7181.0229) (4170.5038 7184.1069) (4173.5115 7186.4427) (4175.313 7187.0382) (4176.1679 7185.3588)
      (4176.626 7181.5725) (4177.3282 7176.5191) (4178.6412 7171.4809) (4180.687 7167.771) (4183.2061 7166.4122)
      (4185.7252 7167.771) (4187.771 7171.4809) (4189.0992 7176.5191) (4189.7863 7181.5725) (4190.2443 7185.3588)
      (4191.0992 7187.0382) (4192.9008 7186.4427) (4195.9084 7184.1069) (4199.9695 7181.0229) (4204.4733 7178.3969)
      (4208.5344 7177.2214) (4211.2672 7178.0458) (4212.0916 7180.7786) (4210.916 7184.8397) (4208.2901 7189.3435)
      (4205.2061 7193.4046) (4202.8702 7196.4122) (4202.2748 7198.2137) (4203.9542 7199.0687) (4207.7405 7199.5267)
      (4212.7939 7200.2137) (4217.8321 7201.542) (4221.542 7203.5878) (4222.9008 7206.1069) (4221.542 7208.626)
      (4217.8321 7210.6718) (4212.7939 7211.9847) (4207.7405 7212.687) (4203.9542 7213.145) (4202.2748 7214.0)
      (4202.8702 7215.8015) (4205.2061 7218.8092) (4208.2901 7222.8702) (4210.916 7227.374) (4212.0916 7231.4351)
      (4211.2672 7234.1679) (4208.5344 7234.9924) (4204.4733 7233.8168) (4199.9695 7231.1908) (4195.9084 7228.1069)
      (4192.9008 7225.771) (4191.0992 7225.1756) (4190.2443 7226.855) (4189.7863 7230.6412) (4189.0992 7235.6947)
      (4187.771 7240.7328) (4185.7252 7244.4427) (4183.2061 7245.8015) (4180.687 7244.4427) (4178.6412 7240.7328)
      (4177.3282 7235.6947) (4176.626 7230.6412) (4176.1679 7226.855) (4175.313 7225.1756) (4173.5115 7225.771)
      (4170.5038 7228.1069) (4166.4427 7231.1908) (4161.9389 7233.8168) (4157.8779 7234.9924) (4155.145 7234.1679)
      (4154.3206 7231.4351) (4155.4962 7227.374) (4158.1221 7222.8702) (4161.2061 7218.8092) (4163.542 7215.8015)
      (4164.1374 7214.0) (4162.458 7213.145) (4158.6718 7212.687) (4153.6183 7211.9847) (4148.5802 7210.6718)
      (4144.8702 7208.626)
    ))
    ; P3063 -- see feature_dimensions_mm.csv
    ("06_ORNAMENT" 1 (
      (4149.3435 3960.0305) (4160.4427 3959.6489) (4177.9389 3960.1527) (4174.687 3953.2519) (4165.0382 3956.4885)
      (4154.5954 3959.1603)
    ))
    ; P3064 -- see feature_dimensions_mm.csv
    ("06_ORNAMENT" 1 (
      (4152.9618 5736.9924) (4153.7557 5744.1069) (4155.7405 5754.0763) (4158.4733 5763.9695) (4161.8321 5773.4656)
      (4165.6489 5782.2901) (4169.7557 5790.1069) (4174.0305 5796.6107) (4178.3206 5801.5267) (4183.2672 5804.7634)
      (4189.2824 5806.5649) (4195.8931 5807.1298) (4202.5954 5806.6718) (4208.9008 5805.3893) (4214.3053 5803.4656)
      (4218.3206 5801.084) (4220.458 5798.4733) (4220.1374 5795.374) (4217.5725 5791.4809) (4213.4656 5786.9466)
      (4208.5496 5781.8626) (4203.5115 5776.3969) (4199.0687 5770.6412) (4195.9389 5764.7176) (4195.3893 5761.8168)
      (4183.7252 5755.5725) (4157.3435 5739.8779)
    ))
    ; P3065 -- see feature_dimensions_mm.csv
    ("06_ORNAMENT" 1 (
      (4174.0763 7374.0458) (4174.7786 7370.5496) (4176.7481 7367.5878) (4179.7099 7365.6183) (4183.2061 7364.916)
      (4186.7023 7365.6183) (4189.6641 7367.5878) (4191.6336 7370.5496) (4192.3359 7374.0458) (4191.6336 7377.542)
      (4189.6641 7380.5038) (4186.7023 7382.4733) (4183.2061 7383.1756) (4179.7099 7382.4733) (4176.7481 7380.5038)
      (4174.7786 7377.542)
    ))
    ; P3066 -- see feature_dimensions_mm.csv
    ("06_ORNAMENT" 1 (
      (4174.0763 7206.1069) (4174.7786 7202.6107) (4176.7481 7199.6489) (4179.7099 7197.6794) (4183.2061 7196.9771)
      (4186.7023 7197.6794) (4189.6641 7199.6489) (4191.6336 7202.6107) (4192.3359 7206.1069) (4191.6336 7209.6031)
      (4189.6641 7212.5649) (4186.7023 7214.5344) (4183.2061 7215.2366) (4179.7099 7214.5344) (4176.7481 7212.5649)
      (4174.7786 7209.6031)
    ))
    ; P3067 -- see feature_dimensions_mm.csv
    ("06_ORNAMENT" 1 (
      (4180.5802 3950.8855) (4190.9008 3960.6718) (4202.7176 3961.6183) (4194.5496 3947.6641) (4193.0992 3944.9008)
      (4184.4275 3949.313)
    ))
    ; P3068 -- see feature_dimensions_mm.csv
    ("06_ORNAMENT" 1 (
      (4247.6489 5206.0611) (4248.0916 5215.5725) (4249.4351 5224.8397) (4251.9237 5234.3206) (4255.3435 5243.7099)
      (4259.542 5252.7328) (4264.3053 5261.1145) (4269.4504 5268.5344) (4274.7939 5274.7176) (4280.1527 5279.3893)
      (4286.3359 5282.458) (4293.8626 5284.1679) (4302.1221 5284.7176) (4310.5038 5284.2901) (4318.3664 5283.0534)
      (4325.1298 5281.2214) (4330.1527 5278.9771) (4332.8244 5276.4885) (4332.4122 5273.542) (4329.2061 5269.8473)
      (4324.0916 5265.5267) (4317.9389 5260.7176) (4311.6489 5255.5115) (4306.0916 5250.0458) (4302.1679 5244.4275)
      (4300.7634 5238.7786) (4301.6947 5232.4122) (4304.0305 5224.916) (4307.5725 5216.8244) (4312.0763 5208.687)
      (4317.2977 5201.0534) (4323.0382 5194.458) (4329.0534 5189.4504) (4335.1145 5186.5649) (4341.8321 5185.7252)
      (4345.6031 5186.0305) (4329.2061 5172.3206) (4288.5802 5136.3511) (4278.0916 5126.5344) (4268.7023 5134.3511)
      (4262.2595 5143.2366) (4257.1603 5153.0229) (4253.2977 5163.4504) (4250.5191 5174.229) (4248.7481 5185.1145)
      (4247.8168 5195.8168)
    ))
    ; P3069 -- see feature_dimensions_mm.csv
    ("06_ORNAMENT" 1 (
      (4247.6489 4335.8321) (4248.0916 4345.3435) (4249.4351 4354.6107) (4250.8397 4359.9389) (4259.542 4351.145)
      (4257.1756 4377.4046) (4259.542 4382.5038) (4264.3053 4390.8855) (4269.4504 4398.3053) (4274.7939 4404.4885)
      (4280.1527 4409.1603) (4286.3359 4412.229) (4293.8626 4413.9389) (4302.1221 4414.4885) (4310.5038 4414.0611)
      (4318.3664 4412.8244) (4325.1298 4410.9924) (4330.1527 4408.7481) (4332.8244 4406.2595) (4332.4122 4403.313)
      (4329.2061 4399.6183) (4324.0916 4395.2977) (4317.9389 4390.4885) (4311.6489 4385.2824) (4306.0916 4379.8168)
      (4302.1679 4374.1985) (4300.7634 4368.5496) (4301.6947 4362.1832) (4304.0305 4354.687) (4307.5725 4346.5954)
      (4312.0763 4338.458) (4317.2977 4330.8244) (4323.0382 4324.229) (4329.0534 4319.2214) (4335.1145 4316.3359)
      (4341.8321 4315.4962) (4349.6641 4316.1374) (4358.1985 4318.0916) (4367.0382 4321.2366) (4373.6183 4324.3817)
      (4370.4885 4317.1603) (4366.4122 4304.7328) (4362.6565 4290.7023) (4358.7481 4274.3359) (4355.2977 4256.6107)
      (4352.916 4238.4733) (4352.3664 4224.458) (4350.6412 4222.3053) (4343.6183 4225.542) (4327.6794 4232.2137)
      (4310.2137 4239.6183) (4293.2519 4247.5267) (4278.7481 4255.771) (4268.7023 4264.1221) (4262.2595 4273.0076)
      (4257.1603 4282.7939) (4253.2977 4293.2214) (4250.5191 4304.0) (4248.7481 4314.8855) (4247.8168 4325.5878)
    ))
    ; P3070 -- see feature_dimensions_mm.csv
    ("06_ORNAMENT" 1 (
      (4274.7328 4204.1985) (4282.5802 4203.9237) (4310.0916 4204.7023) (4334.3053 4206.6565) (4339.0382 4207.313)
      (4325.4504 4189.5878) (4312.7481 4188.9466) (4300.229 4186.8855) (4289.7252 4183.4809) (4288.4733 4186.0458)
      (4281.6794 4196.0)
    ))
    ; P3071 -- see feature_dimensions_mm.csv
    ("06_ORNAMENT" 1 (
      (4347.1298 4094.2748) (4358.9008 4110.6107) (4366.5191 4121.6794) (4373.5725 4120.4427) (4374.1832 4120.2595)
      (4355.8779 4103.0229)
    ))
    ; P3072 -- see feature_dimensions_mm.csv
    ("06_ORNAMENT" 1 (
      (4369.9084 5481.6641) (4370.229 5490.687) (4371.2214 5499.4656) (4373.0382 5508.4427) (4375.5573 5517.3435)
      (4378.626 5525.8931) (4382.1221 5533.8321) (4385.8931 5540.855) (4389.8168 5546.7176) (4393.7405 5551.145)
      (4398.2748 5554.0458) (4403.7863 5555.6794) (4409.8473 5556.1985) (4416.0 5555.7863) (4421.771 5554.626)
      (4426.7176 5552.8855) (4430.4122 5550.7481) (4432.3664 5548.3969) (4432.0611 5545.6031) (4429.7099 5542.1069)
      (4425.9542 5538.0153) (4421.4504 5533.4504) (4416.8397 5528.5191) (4412.7634 5523.3435) (4409.8931 5518.0153)
      (4408.855 5512.6718) (4409.542 5506.6412) (4411.2519 5499.5267) (4413.8473 5491.8626) (4416.626 5485.3893)
      (4410.2748 5475.5267) (4396.7176 5451.9237) (4384.4122 5427.6489) (4381.4046 5420.7634) (4380.626 5422.1527)
      (4376.8855 5431.4351) (4374.0458 5441.313) (4372.0153 5451.5267) (4370.7023 5461.8321) (4370.0305 5471.9695)
    ))
    ; P3073 -- see feature_dimensions_mm.csv
    ("06_ORNAMENT" 1 (
      (4384.7939 3789.5267) (4386.1679 3772.2595) (4390.0458 3757.5878) (4396.9466 3746.5649) (4408.9924 3739.1603)
      (4426.6107 3734.3969) (4447.7557 3731.8626) (4470.3511 3731.0992) (4492.3511 3731.7099) (4511.7252 3733.2519)
      (4526.4122 3735.2977) (4534.3511 3737.4046) (4534.7328 3739.9847) (4529.145 3743.6336) (4519.1756 3748.1679)
      (4506.4122 3753.4351) (4492.4427 3759.2824) (4478.8702 3765.5267) (4467.2672 3772.0305) (4459.2366 3778.626)
      (4454.0763 3785.6336) (4450.0 3793.374) (4446.9008 3801.6031) (4444.7023 3810.1069) (4443.2672 3818.7023)
      (4442.5344 3827.145) (4442.3969 3835.2366) (4442.7481 3842.7481) (4443.8321 3850.0611) (4445.8168 3857.542)
      (4448.5496 3864.9618) (4451.9084 3872.0916) (4455.7252 3878.7023) (4459.8321 3884.5649) (4464.1069 3889.4504)
      (4468.3969 3893.1298) (4473.3435 3895.5573) (4479.3588 3896.9008) (4485.9695 3897.3435) (4492.6718 3896.9924)
      (4498.9771 3896.0305) (4504.3817 3894.5802) (4508.3969 3892.7939) (4510.5344 3890.8397) (4510.2137 3888.5191)
      (4507.6489 3885.6031) (4503.542 3882.1985) (4498.626 3878.3817) (4493.5878 3874.2748) (4489.145 3869.9542)
      (4486.0153 3865.5267) (4484.8855 3861.0687) (4485.6336 3856.0458) (4487.5115 3850.1221) (4490.3359 3843.7252)
      (4493.9389 3837.313) (4498.1221 3831.2824) (4502.7023 3826.0763) (4507.5115 3822.1221) (4512.3664 3819.8473)
      (4517.7405 3819.1756) (4524.0 3819.6794) (4530.8397 3821.2366) (4537.9084 3823.7099) (4544.8702 3826.9924)
      (4551.4046 3830.9618) (4557.1603 3835.4809) (4561.8321 3840.458) (4565.8321 3846.2595) (4569.6641 3853.1756)
      (4573.0992 3860.9313) (4575.9237 3869.2214) (4577.8931 3877.8015) (4578.7939 3886.3511) (4578.3969 3894.6107)
      (4576.4885 3902.2901) (4572.7634 3909.8321) (4567.3282 3917.6947) (4560.5191 3925.6183) (4552.6718 3933.3435)
      (4544.1374 3940.626) (4535.2672 3947.2214) (4526.3969 3952.8397) (4517.8626 3957.2519) (4509.2214 3960.8244)
      (4499.9695 3963.9847) (4490.3206 3966.4885) (4480.5344 3968.1221) (4470.8244 3968.7023) (4461.4351 3967.9847)
      (4452.6107 3965.771) (4444.5802 3961.8321) (4437.0687 3956.0305) (4429.7557 3948.5191) (4422.7481 3939.4962)
      (4416.1832 3929.1908) (4410.1985 3917.8168) (4404.9008 3905.5878) (4400.4427 3892.7023) (4396.9466 3879.3893)
      (4393.7252 3864.3511) (4390.3817 3846.8244) (4387.4198 3827.8321) (4385.3893 3808.3969)
    ))
    ; P3074 -- see feature_dimensions_mm.csv
    ("06_ORNAMENT" 1 (
      (4632.0611 7374.0458) (4633.4198 7371.5267) (4637.1298 7369.4809) (4642.1679 7368.1527) (4647.2214 7367.4656)
      (4651.0076 7367.0076) (4652.687 7366.1527) (4652.0916 7364.3511) (4649.7557 7361.3435) (4646.6718 7357.2824)
      (4644.0458 7352.7786) (4642.8702 7348.7176) (4643.6947 7345.9847) (4646.4275 7345.1603) (4650.4885 7346.3359)
      (4654.9924 7348.9618) (4659.0534 7352.0458) (4662.0611 7354.3817) (4663.8626 7354.9771) (4664.7176 7353.2977)
      (4665.1756 7349.5115) (4665.8779 7344.458) (4667.1908 7339.4198) (4669.2366 7335.7099) (4671.7557 7334.3511)
      (4674.2748 7335.7099) (4676.3206 7339.4198) (4677.6489 7344.458) (4678.3359 7349.5115) (4678.7939 7353.2977)
      (4679.6489 7354.9771) (4681.4504 7354.3817) (4684.458 7352.0458) (4688.5191 7348.9618) (4693.0229 7346.3359)
      (4697.084 7345.1603) (4699.8168 7345.9847) (4700.6412 7348.7176) (4699.4656 7352.7786) (4696.8397 7357.2824)
      (4693.7557 7361.3435) (4691.4198 7364.3511) (4690.8244 7366.1527) (4692.5038 7367.0076) (4696.2901 7367.4656)
      (4701.3435 7368.1527) (4706.3817 7369.4809) (4710.0916 7371.5267) (4711.4504 7374.0458) (4710.0916 7376.5649)
      (4706.3817 7378.6107) (4701.3435 7379.9237) (4696.2901 7380.626) (4692.5038 7381.084) (4690.8244 7381.9389)
      (4691.4198 7383.7405) (4693.7557 7386.7481) (4696.8397 7390.8092) (4699.4656 7395.313) (4700.6412 7399.374)
      (4699.8168 7402.1069) (4697.084 7402.9313) (4693.0229 7401.7557) (4688.5191 7399.1298) (4684.458 7396.0458)
      (4681.4504 7393.7099) (4679.6489 7393.1145) (4678.7939 7394.7939) (4678.3359 7398.5802) (4677.6489 7403.6336)
      (4676.3206 7408.6718) (4674.2748 7412.3817) (4671.7557 7413.7405) (4669.2366 7412.3817) (4667.1908 7408.6718)
      (4665.8779 7403.6336) (4665.1756 7398.5802) (4664.7176 7394.7939) (4663.8626 7393.1145) (4662.0611 7393.7099)
      (4659.0534 7396.0458) (4654.9924 7399.1298) (4650.4885 7401.7557) (4646.4275 7402.9313) (4643.6947 7402.1069)
      (4642.8702 7399.374) (4644.0458 7395.313) (4646.6718 7390.8092) (4649.7557 7386.7481) (4652.0916 7383.7405)
      (4652.687 7381.9389) (4651.0076 7381.084) (4647.2214 7380.626) (4642.1679 7379.9237) (4637.1298 7378.6107)
      (4633.4198 7376.5649)
    ))
    ; P3075 -- see feature_dimensions_mm.csv
    ("06_ORNAMENT" 1 (
      (4632.0611 7206.1069) (4633.4198 7203.5878) (4637.1298 7201.542) (4642.1679 7200.2137) (4647.2214 7199.5267)
      (4651.0076 7199.0687) (4652.687 7198.2137) (4652.0916 7196.4122) (4649.7557 7193.4046) (4646.6718 7189.3435)
      (4644.0458 7184.8397) (4642.8702 7180.7786) (4643.6947 7178.0458) (4646.4275 7177.2214) (4650.4885 7178.3969)
      (4654.9924 7181.0229) (4659.0534 7184.1069) (4662.0611 7186.4427) (4663.8626 7187.0382) (4664.7176 7185.3588)
      (4665.1756 7181.5725) (4665.8779 7176.5191) (4667.1908 7171.4809) (4669.2366 7167.771) (4671.7557 7166.4122)
      (4674.2748 7167.771) (4676.3206 7171.4809) (4677.6489 7176.5191) (4678.3359 7181.5725) (4678.7939 7185.3588)
      (4679.6489 7187.0382) (4681.4504 7186.4427) (4684.458 7184.1069) (4688.5191 7181.0229) (4693.0229 7178.3969)
      (4697.084 7177.2214) (4699.8168 7178.0458) (4700.6412 7180.7786) (4699.4656 7184.8397) (4696.8397 7189.3435)
      (4693.7557 7193.4046) (4691.4198 7196.4122) (4690.8244 7198.2137) (4692.5038 7199.0687) (4696.2901 7199.5267)
      (4701.3435 7200.2137) (4706.3817 7201.542) (4710.0916 7203.5878) (4711.4504 7206.1069) (4710.0916 7208.626)
      (4706.3817 7210.6718) (4701.3435 7211.9847) (4696.2901 7212.687) (4692.5038 7213.145) (4690.8244 7214.0)
      (4691.4198 7215.8015) (4693.7557 7218.8092) (4696.8397 7222.8702) (4699.4656 7227.374) (4700.6412 7231.4351)
      (4699.8168 7234.1679) (4697.084 7234.9924) (4693.0229 7233.8168) (4688.5191 7231.1908) (4684.458 7228.1069)
      (4681.4504 7225.771) (4679.6489 7225.1756) (4678.7939 7226.855) (4678.3359 7230.6412) (4677.6489 7235.6947)
      (4676.3206 7240.7328) (4674.2748 7244.4427) (4671.7557 7245.8015) (4669.2366 7244.4427) (4667.1908 7240.7328)
      (4665.8779 7235.6947) (4665.1756 7230.6412) (4664.7176 7226.855) (4663.8626 7225.1756) (4662.0611 7225.771)
      (4659.0534 7228.1069) (4654.9924 7231.1908) (4650.4885 7233.8168) (4646.4275 7234.9924) (4643.6947 7234.1679)
      (4642.8702 7231.4351) (4644.0458 7227.374) (4646.6718 7222.8702) (4649.7557 7218.8092) (4652.0916 7215.8015)
      (4652.687 7214.0) (4651.0076 7213.145) (4647.2214 7212.687) (4642.1679 7211.9847) (4637.1298 7210.6718)
      (4633.4198 7208.626)
    ))
    ; P3076 -- see feature_dimensions_mm.csv
    ("06_ORNAMENT" 1 (
      (4662.626 7374.0458) (4663.3282 7370.5496) (4665.2977 7367.5878) (4668.2595 7365.6183) (4671.7557 7364.916)
      (4675.2519 7365.6183) (4678.2137 7367.5878) (4680.1832 7370.5496) (4680.8855 7374.0458) (4680.1832 7377.542)
      (4678.2137 7380.5038) (4675.2519 7382.4733) (4671.7557 7383.1756) (4668.2595 7382.4733) (4665.2977 7380.5038)
      (4663.3282 7377.542)
    ))
    ; P3077 -- see feature_dimensions_mm.csv
    ("06_ORNAMENT" 1 (
      (4662.626 7206.1069) (4663.3282 7202.6107) (4665.2977 7199.6489) (4668.2595 7197.6794) (4671.7557 7196.9771)
      (4675.2519 7197.6794) (4678.2137 7199.6489) (4680.1832 7202.6107) (4680.8855 7206.1069) (4680.1832 7209.6031)
      (4678.2137 7212.5649) (4675.2519 7214.5344) (4671.7557 7215.2366) (4668.2595 7214.5344) (4665.2977 7212.5649)
      (4663.3282 7209.6031)
    ))
    ; P3078 -- see feature_dimensions_mm.csv
    ("06_ORNAMENT" 1 (
      (8851.2366 3120.2901) (8852.0763 3081.4962) (8854.5191 3041.1145) (8858.3969 2999.6947) (8863.542 2957.771)
      (8869.8168 2915.9389) (8877.0229 2874.7176) (8885.0382 2834.687) (8893.6641 2796.3969) (8902.7786 2760.4122)
      (8912.1832 2727.2672) (8921.7557 2697.5267) (8931.2977 2671.7557) (8932.5802 2702.2137) (8932.8244 2735.8626)
      (8932.0153 2772.1679) (8930.1832 2810.5802) (8927.313 2850.5649) (8923.4046 2891.5573) (8918.458 2933.0382)
      (8912.4733 2974.4275) (8905.4656 3015.2214) (8904.2137 3021.374) (8904.4122 3020.8397) (8919.4656 2984.8092)
      (8935.5725 2949.145) (8952.4427 2914.3206) (8969.771 2880.7786) (8987.2824 2848.9618) (9004.7023 2819.3435)
      (9021.7252 2792.3511) (9038.0611 2768.4427) (9053.4351 2748.0916) (9047.313 2775.6947) (9039.4046 2805.8626)
      (9029.8779 2838.1069) (9018.8397 2871.9389) (9006.4275 2906.8855) (8992.7786 2942.458) (8978.0305 2978.1527)
      (8962.3053 3013.4962) (8945.7405 3048.0) (8928.4733 3081.1756) (8927.0687 3083.6336) (8929.374 3080.7023)
      (8953.1756 3052.5954) (8978.2443 3024.8855) (9004.1832 2997.8779) (9030.5649 2971.8779) (9056.9924 2947.2366)
      (9083.0534 2924.229) (9108.3511 2903.1908) (9132.4733 2884.4122) (9155.0229 2868.2443) (9175.5725 2854.9618)
      (9161.3893 2878.0611) (9144.7786 2902.9008) (9126.0153 2929.0687) (9105.3588 2956.1832) (9083.084 2983.8168)
      (9059.4656 3011.6031) (9034.7786 3039.1145) (9009.2977 3065.9695) (8983.2824 3091.7557) (8957.0229 3116.0916)
      (8935.0382 3134.9313) (8938.229 3132.9618) (8970.8244 3114.5496) (9004.9924 3096.8397) (9040.1985 3079.9542)
      (9075.9389 3064.0458) (9111.7099 3049.2672) (9146.9618 3035.7557) (9181.2061 3023.6641) (9213.9237 3013.1298)
      (9244.5954 3004.3053) (9272.687 2997.3435) (9297.7099 2992.3664) (9274.7786 3008.9008) (9248.8092 3026.1527)
      (9220.229 3043.8931) (9189.4809 3061.8168) (9156.9618 3079.6489) (9123.1145 3097.1145) (9088.3511 3113.9542)
      (9053.0992 3129.8779) (9017.771 3144.6107) (8982.8092 3157.8779) (8977.6183 3159.6336) (8999.4962 3155.7863)
      (9040.4122 3149.9695) (9082.0916 3145.2824) (9123.9542 3141.6947) (9165.4351 3139.1908) (9205.9542 3137.7099)
      (9244.9466 3137.2672) (9281.8168 3137.7863) (9316.0153 3139.2824) (9346.9466 3141.7099) (9374.0458 3145.0382)
      (9344.916 3153.3282) (9312.4733 3161.3435) (9277.2061 3168.9618) (9239.6794 3176.0611) (9200.3817 3182.5191)
      (9159.8779 3188.1985) (9118.6718 3192.9771) (9077.2977 3196.7328) (9036.2748 3199.3435) (8996.1374 3200.687)
      (8957.4198 3200.626) (8920.626 3199.0534) (8886.3053 3195.8321) (8854.9618 3190.8397) (8852.1374 3156.916)
    ))
    ; P3079 -- see feature_dimensions_mm.csv
    ("06_ORNAMENT" 1 (
      (8967.1756 5138.2137) (8968.3969 5132.0916) (8971.8779 5126.8855) (8977.0687 5123.4046) (8983.2061 5122.1832)
      (8989.3435 5123.4046) (8994.5344 5126.8855) (8998.0153 5132.0916) (8999.2366 5138.2137) (8998.0153 5144.3511)
      (8994.5344 5149.5573) (8989.3435 5153.0229) (8983.2061 5154.2443) (8977.0687 5153.0229) (8971.8779 5149.5573)
      (8968.3969 5144.3511)
    ))
    ; P3080 -- see feature_dimensions_mm.csv
    ("06_ORNAMENT" 1 (
      (8967.1756 5061.8779) (8968.3969 5055.7557) (8971.8779 5050.5496) (8977.0687 5047.0687) (8983.2061 5045.8473)
      (8989.3435 5047.0687) (8994.5344 5050.5496) (8998.0153 5055.7557) (8999.2366 5061.8779) (8998.0153 5068.0153)
      (8994.5344 5073.2214) (8989.3435 5076.687) (8983.2061 5077.9084) (8977.0687 5076.687) (8971.8779 5073.2214)
      (8968.3969 5068.0153)
    ))
    ; P3081 -- see feature_dimensions_mm.csv
    ("06_ORNAMENT" 1 (
      (8967.1756 4985.542) (8968.3969 4979.4198) (8971.8779 4974.2137) (8977.0687 4970.7328) (8983.2061 4969.5115)
      (8989.3435 4970.7328) (8994.5344 4974.2137) (8998.0153 4979.4198) (8999.2366 4985.542) (8998.0153 4991.6794)
      (8994.5344 4996.8855) (8989.3435 5000.3511) (8983.2061 5001.5725) (8977.0687 5000.3511) (8971.8779 4996.8855)
      (8968.3969 4991.6794)
    ))
    ; P3082 -- see feature_dimensions_mm.csv
    ("06_ORNAMENT" 1 (
      (8967.1756 4909.2061) (8968.3969 4903.084) (8971.8779 4897.8779) (8977.0687 4894.3969) (8983.2061 4893.1756)
      (8989.3435 4894.3969) (8994.5344 4897.8779) (8998.0153 4903.084) (8999.2366 4909.2061) (8998.0153 4915.3435)
      (8994.5344 4920.5496) (8989.3435 4924.0153) (8983.2061 4925.2366) (8977.0687 4924.0153) (8971.8779 4920.5496)
      (8968.3969 4915.3435)
    ))
    ; P3083 -- see feature_dimensions_mm.csv
    ("06_ORNAMENT" 1 (
      (8967.1756 4832.8702) (8968.3969 4826.7481) (8971.8779 4821.542) (8977.0687 4818.0611) (8983.2061 4816.8397)
      (8989.3435 4818.0611) (8994.5344 4821.542) (8998.0153 4826.7481) (8999.2366 4832.8702) (8998.0153 4839.0076)
      (8994.5344 4844.2137) (8989.3435 4847.6794) (8983.2061 4848.9008) (8977.0687 4847.6794) (8971.8779 4844.2137)
      (8968.3969 4839.0076)
    ))
    ; P3084 -- see feature_dimensions_mm.csv
    ("06_ORNAMENT" 1 (
      (8967.1756 4756.5344) (8968.3969 4750.4122) (8971.8779 4745.2061) (8974.5496 4743.4046) (8974.2137 4741.8321)
      (8971.6183 4722.1374) (8970.7481 4702.2901) (8971.2519 4690.626) (8968.3969 4686.3359) (8967.1756 4680.1985)
      (8968.3969 4674.0763) (8971.8779 4668.8702) (8973.542 4667.7405) (8974.2137 4662.7481) (8978.5038 4643.3435)
      (8984.4885 4624.3969) (8986.626 4619.2214) (8983.2061 4619.8931) (8977.0687 4618.6718) (8971.8779 4615.2061)
      (8968.3969 4610.0) (8967.1756 4603.8626) (8968.3969 4597.7405) (8971.8779 4592.5344) (8977.0687 4589.0534)
      (8983.2061 4587.8321) (8989.3435 4589.0534) (8994.5344 4592.5344) (8997.1145 4596.3817) (9001.2519 4588.4275)
      (9011.9389 4571.6794) (9024.0305 4555.9084) (9037.4504 4541.2672) (9052.0916 4527.8473) (9067.8626 4515.7557)
      (9084.6107 4505.0687) (9102.229 4495.9084) (9120.5802 4488.3053) (9139.5267 4482.3206) (9158.9313 4478.0305)
      (9178.626 4475.4351) (9198.4733 4474.5649) (9218.3206 4475.4351) (9238.0153 4478.0305) (9257.4198 4482.3206)
      (9276.3664 4488.3053) (9294.7176 4495.9084) (9312.3359 4505.0687) (9329.084 4515.7557) (9344.855 4527.8473)
      (9359.4962 4541.2672) (9372.916 4555.9084) (9385.0076 4571.6794) (9395.6947 4588.4275) (9399.8321 4596.3817)
      (9402.4122 4592.5344) (9407.6031 4589.0534) (9413.7405 4587.8321) (9419.8779 4589.0534) (9425.0687 4592.5344)
      (9428.5496 4597.7405) (9429.771 4603.8626) (9428.5496 4610.0) (9425.0687 4615.2061) (9419.8779 4618.6718)
      (9413.7405 4619.8931) (9410.3206 4619.2214) (9412.458 4624.3969) (9418.4427 4643.3435) (9422.7328 4662.7481)
      (9423.4046 4667.7405) (9425.0687 4668.8702) (9428.5496 4674.0763) (9429.771 4680.1985) (9428.5496 4686.3359)
      (9425.6947 4690.626) (9426.1985 4702.2901) (9425.3282 4722.1374) (9422.7328 4741.8321) (9422.3969 4743.4046)
      (9425.0687 4745.2061) (9428.5496 4750.4122) (9429.771 4756.5344) (9428.5496 4762.6718) (9425.0687 4767.8779)
      (9419.8779 4771.3435) (9414.9313 4772.3359) (9412.458 4780.1832) (9404.855 4798.5344) (9395.6947 4816.1527)
      (9385.0076 4832.9008) (9372.916 4848.6718) (9359.4962 4863.313) (9344.855 4876.7328) (9329.084 4888.8244)
      (9312.3359 4899.5115) (9294.7176 4908.6718) (9276.3664 4916.2748) (9257.4198 4922.2595) (9238.0153 4926.5496)
      (9218.3206 4929.145) (9198.4733 4930.0153) (9178.626 4929.145) (9158.9313 4926.5496) (9139.5267 4922.2595)
      (9120.5802 4916.2748) (9102.229 4908.6718) (9084.6107 4899.5115) (9067.8626 4888.8244) (9052.0916 4876.7328)
      (9037.4504 4863.313) (9024.0305 4848.6718) (9011.9389 4832.9008) (9001.2519 4816.1527) (8992.0916 4798.5344)
      (8984.4885 4780.1832) (8982.0153 4772.3359) (8977.0687 4771.3435) (8971.8779 4767.8779) (8968.3969 4762.6718)
    ))
    ; P3085 -- see feature_dimensions_mm.csv
    ("06_ORNAMENT" 1 (
      (8967.1756 4527.5267) (8968.3969 4521.4046) (8971.8779 4516.1985) (8977.0687 4512.7176) (8983.2061 4511.4962)
      (8989.3435 4512.7176) (8994.5344 4516.1985) (8998.0153 4521.4046) (8999.2366 4527.5267) (8998.0153 4533.6641)
      (8994.5344 4538.8702) (8989.3435 4542.3359) (8983.2061 4543.5573) (8977.0687 4542.3359) (8971.8779 4538.8702)
      (8968.3969 4533.6641)
    ))
    ; P3086 -- see feature_dimensions_mm.csv
    ("06_ORNAMENT" 1 (
      (8967.1756 4374.855) (8968.3969 4368.7328) (8971.8779 4363.5267) (8977.0687 4360.0458) (8983.2061 4358.8244)
      (8989.3435 4360.0458) (8994.5344 4363.5267) (8998.0153 4368.7328) (8999.2366 4374.855) (8998.0153 4380.9924)
      (8994.5344 4386.1985) (8989.3435 4389.6641) (8983.2061 4390.8855) (8977.0687 4389.6641) (8971.8779 4386.1985)
      (8968.3969 4380.9924)
    ))
    ; P3087 -- see feature_dimensions_mm.csv
    ("06_ORNAMENT" 1 (
      (8967.1756 4298.5191) (8968.3969 4292.3969) (8971.8779 4287.1908) (8977.0687 4283.7099) (8983.2061 4282.4885)
      (8989.3435 4283.7099) (8994.5344 4287.1908) (8998.0153 4292.3969) (8999.2366 4298.5191) (8998.0153 4304.6565)
      (8994.5344 4309.8626) (8989.3435 4313.3282) (8983.2061 4314.5496) (8977.0687 4313.3282) (8971.8779 4309.8626)
      (8968.3969 4304.6565)
    ))
    ; P3088 -- see feature_dimensions_mm.csv
    ("06_ORNAMENT" 1 (
      (8967.1756 4222.1832) (8968.3969 4216.0611) (8971.8779 4210.855) (8977.0687 4207.374) (8983.2061 4206.1527)
      (8989.3435 4207.374) (8994.5344 4210.855) (8998.0153 4216.0611) (8999.2366 4222.1832) (8998.0153 4228.3206)
      (8994.5344 4233.5267) (8989.3435 4236.9924) (8983.2061 4238.2137) (8977.0687 4236.9924) (8971.8779 4233.5267)
      (8968.3969 4228.3206)
    ))
    ; P3089 -- see feature_dimensions_mm.csv
    ("06_ORNAMENT" 1 (
      (8967.1756 3916.8397) (8968.3969 3910.7176) (8971.8779 3905.5115) (8977.0687 3902.0305) (8983.2061 3900.8092)
      (8989.3435 3902.0305) (8994.5344 3905.5115) (8998.0153 3910.7176) (8999.2366 3916.8397) (8998.0153 3922.9771)
      (8994.5344 3928.1832) (8989.3435 3931.6489) (8983.2061 3932.8702) (8977.0687 3931.6489) (8971.8779 3928.1832)
      (8968.3969 3922.9771)
    ))
    ; P3090 -- see feature_dimensions_mm.csv
    ("06_ORNAMENT" 1 (
      (8977.8015 4106.8702) (8979.0229 4102.3359) (8982.3359 4099.0229) (8986.8702 4097.8015) (8991.4046 4099.0229)
      (8994.7176 4102.3359) (8995.9389 4106.8702) (8994.7176 4111.4046) (8991.4046 4114.7176) (8986.8702 4115.9389)
      (8982.3359 4114.7176) (8979.0229 4111.4046)
    ))
    ; P3091 -- see feature_dimensions_mm.csv
    ("06_ORNAMENT" 1 (
      (8993.9084 4783.2672) (8995.1298 4778.7328) (8998.4427 4775.4198) (9002.9771 4774.1985) (9007.5115 4775.4198)
      (9010.8244 4778.7328) (9012.0458 4783.2672) (9010.8244 4787.8015) (9007.5115 4791.1145) (9002.9771 4792.3359)
      (8998.4427 4791.1145) (8995.1298 4787.8015)
    ))
    ; P3092 -- see feature_dimensions_mm.csv
    ("06_ORNAMENT" 1 (
      (8993.9084 4621.313) (8995.1298 4616.7786) (8998.4427 4613.4656) (9002.9771 4612.2443) (9007.5115 4613.4656)
      (9010.8244 4616.7786) (9012.0458 4621.313) (9010.8244 4625.8473) (9007.5115 4629.1603) (9002.9771 4630.3817)
      (8998.4427 4629.1603) (8995.1298 4625.8473)
    ))
    ; P3093 -- see feature_dimensions_mm.csv
    ("06_ORNAMENT" 1 (
      (8993.9084 4187.8473) (8995.1298 4183.313) (8998.4427 4180.0) (9002.9771 4178.7786) (9007.5115 4180.0)
      (9010.8244 4183.313) (9012.0458 4187.8473) (9010.8244 4192.3817) (9007.5115 4195.6947) (9002.9771 4196.916)
      (8998.4427 4195.6947) (8995.1298 4192.3817)
    ))
    ; P3094 -- see feature_dimensions_mm.csv
    ("06_ORNAMENT" 1 (
      (8993.9084 4025.8931) (8995.1298 4021.3588) (8998.4427 4018.0458) (9002.9771 4016.8244) (9007.5115 4018.0458)
      (9010.8244 4021.3588) (9012.0458 4025.8931) (9010.8244 4030.4275) (9007.5115 4033.7405) (9002.9771 4034.9618)
      (8998.4427 4033.7405) (8995.1298 4030.4275)
    ))
    ; P3095 -- see feature_dimensions_mm.csv
    ("06_ORNAMENT" 1 (
      (8998.9618 4702.2901) (8999.2672 4699.2977) (9000.1527 4696.3664) (9001.3282 4694.1069) (9001.7252 4685.084)
      (9003.9847 4668.0) (9007.7099 4651.1756) (9012.8855 4634.7481) (9019.4809 4618.8244) (9027.4351 4603.542)
      (9036.687 4589.0076) (9047.1756 4575.3435) (9053.2824 4568.687) (9054.0458 4566.229) (9055.4962 4563.542)
      (9057.4046 4561.2214) (9059.7252 4559.313) (9062.4122 4557.8626) (9064.8702 4557.0992) (9071.5267 4550.9924)
      (9085.1908 4540.5038) (9099.7252 4531.2519) (9115.0076 4523.2977) (9130.9313 4516.7023) (9147.3588 4511.5267)
      (9164.1832 4507.8015) (9181.2672 4505.542) (9190.2901 4505.145) (9192.5496 4503.9695) (9195.4809 4503.0687)
      (9198.4733 4502.7786) (9201.4656 4503.0687) (9204.3969 4503.9695) (9206.6565 4505.145) (9215.6794 4505.542)
      (9232.7634 4507.8015) (9249.5878 4511.5267) (9266.0153 4516.7023) (9281.9389 4523.2977) (9297.2214 4531.2519)
      (9311.7557 4540.5038) (9325.4198 4550.9924) (9332.0763 4557.0992) (9334.5344 4557.8626) (9337.2214 4559.313)
      (9339.542 4561.2214) (9341.4504 4563.542) (9342.9008 4566.229) (9343.6641 4568.687) (9349.771 4575.3435)
      (9360.2595 4589.0076) (9369.5115 4603.542) (9377.4656 4618.8244) (9384.0611 4634.7481) (9389.2366 4651.1756)
      (9392.9618 4668.0) (9395.2214 4685.084) (9395.6183 4694.1069) (9396.7939 4696.3664) (9397.6947 4699.2977)
      (9397.9847 4702.2901) (9397.6947 4705.2824) (9396.7939 4708.2137) (9395.6183 4710.4733) (9395.2214 4719.4962)
      (9392.9618 4736.5802) (9389.2366 4753.4046) (9384.0611 4769.8321) (9377.4656 4785.7557) (9369.5115 4801.0382)
      (9360.2595 4815.5725) (9349.771 4829.2366) (9343.6641 4835.8931) (9342.9008 4838.3511) (9341.4504 4841.0382)
      (9339.542 4843.3588) (9337.2214 4845.2672) (9334.5344 4846.7176) (9332.0763 4847.4809) (9325.4198 4853.5878)
      (9311.7557 4864.0763) (9297.2214 4873.3282) (9281.9389 4881.2824) (9266.0153 4887.8779) (9249.5878 4893.0534)
      (9232.7634 4896.7786) (9215.6794 4899.0382) (9206.6565 4899.4351) (9204.3969 4900.6107) (9201.4656 4901.4962)
      (9198.4733 4901.8015) (9195.4809 4901.4962) (9192.5496 4900.6107) (9190.2901 4899.4351) (9181.2672 4899.0382)
      (9164.1832 4896.7786) (9147.3588 4893.0534) (9130.9313 4887.8779) (9115.0076 4881.2824) (9099.7252 4873.3282)
      (9085.1908 4864.0763) (9071.5267 4853.5878) (9064.8702 4847.4809) (9062.4122 4846.7176) (9059.7252 4845.2672)
      (9057.4046 4843.3588) (9055.4962 4841.0382) (9054.0458 4838.3511) (9053.2824 4835.8931) (9047.1756 4829.2366)
      (9036.687 4815.5725) (9027.4351 4801.0382) (9019.4809 4785.7557) (9012.8855 4769.8321) (9007.7099 4753.4046)
      (9003.9847 4736.5802) (9001.7252 4719.4962) (9001.3282 4710.4733) (9000.1527 4708.2137) (8999.2672 4705.2824)
    ))
    ; P3096 -- see feature_dimensions_mm.csv
    ("06_ORNAMENT" 1 (
      (8998.9618 4106.8702) (8999.2672 4103.8779) (9000.1527 4100.9466) (9001.3282 4098.687) (9001.7252 4089.6641)
      (9003.9847 4072.5802) (9007.7099 4055.7557) (9012.8855 4039.3282) (9019.4809 4023.4046) (9027.4351 4008.1221)
      (9036.687 3993.5878) (9047.1756 3979.9237) (9053.2824 3973.2672) (9054.0458 3970.8092) (9055.4962 3968.1221)
      (9057.4046 3965.8015) (9059.7252 3963.8931) (9062.4122 3962.4427) (9064.8702 3961.6794) (9071.5267 3955.5725)
      (9085.1908 3945.084) (9099.7252 3935.8321) (9115.0076 3927.8779) (9130.9313 3921.2824) (9147.3588 3916.1069)
      (9164.1832 3912.3817) (9181.2672 3910.1221) (9190.2901 3909.7252) (9192.5496 3908.5496) (9195.4809 3907.6489)
      (9198.4733 3907.3588) (9201.4656 3907.6489) (9204.3969 3908.5496) (9206.6565 3909.7252) (9215.6794 3910.1221)
      (9232.7634 3912.3817) (9249.5878 3916.1069) (9266.0153 3921.2824) (9281.9389 3927.8779) (9297.2214 3935.8321)
      (9311.7557 3945.084) (9325.4198 3955.5725) (9332.0763 3961.6794) (9334.5344 3962.4427) (9337.2214 3963.8931)
      (9339.542 3965.8015) (9341.4504 3968.1221) (9342.9008 3970.8092) (9343.6641 3973.2672) (9349.771 3979.9237)
      (9360.2595 3993.5878) (9369.5115 4008.1221) (9377.4656 4023.4046) (9384.0611 4039.3282) (9389.2366 4055.7557)
      (9392.9618 4072.5802) (9395.2214 4089.6641) (9395.6183 4098.687) (9396.7939 4100.9466) (9397.6947 4103.8779)
      (9397.9847 4106.8702) (9397.6947 4109.8626) (9396.7939 4112.7939) (9395.6183 4115.0534) (9395.2214 4124.0763)
      (9392.9618 4141.1603) (9389.2366 4157.9847) (9384.0611 4174.4122) (9377.4656 4190.3359) (9369.5115 4205.6183)
      (9360.2595 4220.1527) (9349.771 4233.8168) (9343.6641 4240.4733) (9342.9008 4242.9313) (9341.4504 4245.6183)
      (9339.542 4247.9389) (9337.2214 4249.8473) (9334.5344 4251.2977) (9332.0763 4252.0611) (9325.4198 4258.1679)
      (9311.7557 4268.6565) (9297.2214 4277.9084) (9281.9389 4285.8626) (9266.0153 4292.458) (9249.5878 4297.6336)
      (9232.7634 4301.3588) (9215.6794 4303.6183) (9206.6565 4304.0153) (9204.3969 4305.1908) (9201.4656 4306.0763)
      (9198.4733 4306.3817) (9195.4809 4306.0763) (9192.5496 4305.1908) (9190.2901 4304.0153) (9181.2672 4303.6183)
      (9164.1832 4301.3588) (9147.3588 4297.6336) (9130.9313 4292.458) (9115.0076 4285.8626) (9099.7252 4277.9084)
      (9085.1908 4268.6565) (9071.5267 4258.1679) (9064.8702 4252.0611) (9062.4122 4251.2977) (9059.7252 4249.8473)
      (9057.4046 4247.9389) (9055.4962 4245.6183) (9054.0458 4242.9313) (9053.2824 4240.4733) (9047.1756 4233.8168)
      (9036.687 4220.1527) (9027.4351 4205.6183) (9019.4809 4190.3359) (9012.8855 4174.4122) (9007.7099 4157.9847)
      (9003.9847 4141.1603) (9001.7252 4124.0763) (9001.3282 4115.0534) (9000.1527 4112.7939) (8999.2672 4109.8626)
    ))
    ; P3097 -- see feature_dimensions_mm.csv
    ("06_ORNAMENT" 1 (
      (9021.374 5007.6336) (9021.7863 5005.0534) (9022.9771 5002.626) (9024.8702 5000.4275) (9027.3282 4998.5954)
      (9030.1679 4997.145) (9033.1908 4996.0916) (9036.229 4995.374) (9039.0687 4994.9313) (9041.5878 4994.6107)
      (9043.6794 4994.2901) (9045.313 4993.8168) (9046.4733 4993.0382) (9047.2519 4991.8779) (9047.7252 4990.2443)
      (9048.0458 4988.1527) (9048.3664 4985.6336) (9048.8092 4982.7939) (9049.5267 4979.7557) (9050.5802 4976.7328)
      (9052.0305 4973.8931) (9053.8626 4971.4351) (9056.0611 4969.542) (9058.4885 4968.3511) (9061.0687 4967.9389)
      (9063.6489 4968.3511) (9066.0763 4969.542) (9068.2748 4971.4351) (9070.1069 4973.8931) (9071.5573 4976.7328)
      (9072.6107 4979.7557) (9073.3282 4982.7939) (9073.771 4985.6336) (9074.0916 4988.1527) (9074.4122 4990.2443)
      (9074.8855 4991.8779) (9075.6641 4993.0382) (9076.8244 4993.8168) (9078.458 4994.2901) (9080.5496 4994.6107)
      (9083.0687 4994.9313) (9085.9084 4995.374) (9088.9466 4996.0916) (9091.9695 4997.145) (9094.8092 4998.5954)
      (9097.2672 5000.4275) (9099.1603 5002.626) (9100.3511 5005.0534) (9100.7634 5007.6336) (9100.3511 5010.2137)
      (9099.1603 5012.6412) (9097.2672 5014.8397) (9094.8092 5016.6718) (9091.9695 5018.1221) (9088.9466 5019.1756)
      (9085.9084 5019.8931) (9083.0687 5020.3359) (9080.5496 5020.6565) (9078.458 5020.9771) (9076.8244 5021.4504)
      (9075.6641 5022.229) (9074.8855 5023.3893) (9074.4122 5025.0229) (9074.0916 5027.1145) (9073.771 5029.6336)
      (9073.3282 5032.4733) (9072.6107 5035.5115) (9071.5573 5038.5344) (9070.1069 5041.374) (9068.2748 5043.8321)
      (9066.0763 5045.7252) (9063.6489 5046.916) (9061.0687 5047.3282) (9058.4885 5046.916) (9056.0611 5045.7252)
      (9053.8626 5043.8321) (9052.0305 5041.374) (9050.5802 5038.5344) (9049.5267 5035.5115) (9048.8092 5032.4733)
      (9048.3664 5029.6336) (9048.0458 5027.1145) (9047.7252 5025.0229) (9047.2519 5023.3893) (9046.4733 5022.229)
      (9045.313 5021.4504) (9043.6794 5020.9771) (9041.5878 5020.6565) (9039.0687 5020.3359) (9036.229 5019.8931)
      (9033.1908 5019.1756) (9030.1679 5018.1221) (9027.3282 5016.6718) (9024.8702 5014.8397) (9022.9771 5012.6412)
      (9021.7863 5010.2137)
    ))
    ; P3098 -- see feature_dimensions_mm.csv
    ("06_ORNAMENT" 1 (
      (9021.9237 5232.9313) (9022.916 5226.7023) (9025.771 5221.084) (9030.229 5216.626) (9035.8473 5213.7557)
      (9042.0763 5212.7786) (9048.3053 5213.7557) (9053.9237 5216.626) (9058.3817 5221.084) (9061.2366 5226.7023)
      (9062.229 5232.9313) (9061.2366 5239.1603) (9058.3817 5244.7786) (9053.9237 5249.2366) (9048.3053 5252.0916)
      (9042.0763 5253.084) (9035.8473 5252.0916) (9030.229 5249.2366) (9025.771 5244.7786) (9022.916 5239.1603)
    ))
    ; P3099 -- see feature_dimensions_mm.csv
    ("06_ORNAMENT" 1 (
      (9021.9237 4767.0687) (9022.916 4760.8397) (9025.771 4755.2214) (9030.229 4750.7634) (9035.8473 4747.9084)
      (9042.0763 4746.916) (9048.3053 4747.9084) (9053.9237 4750.7634) (9058.3817 4755.2214) (9061.2366 4760.8397)
      (9062.229 4767.0687) (9061.2366 4773.2977) (9058.3817 4778.916) (9053.9237 4783.374) (9048.3053 4786.2443)
      (9042.0763 4787.2214) (9035.8473 4786.2443) (9030.229 4783.374) (9025.771 4778.916) (9022.916 4773.2977)
    ))
    ; P3100 -- see feature_dimensions_mm.csv
    ("06_ORNAMENT" 1 (
      (9021.9237 4637.5115) (9022.916 4631.2824) (9025.771 4625.6641) (9030.229 4621.2061) (9035.8473 4618.3359)
      (9042.0763 4617.3588) (9048.3053 4618.3359) (9053.9237 4621.2061) (9058.3817 4625.6641) (9061.2366 4631.2824)
      (9062.229 4637.5115) (9061.2366 4643.7405) (9058.3817 4649.3588) (9053.9237 4653.8168) (9048.3053 4656.6718)
      (9042.0763 4657.6641) (9035.8473 4656.6718) (9030.229 4653.8168) (9025.771 4649.3588) (9022.916 4643.7405)
    ))
    ; P3101 -- see feature_dimensions_mm.csv
    ("06_ORNAMENT" 1 (
      (9021.9237 4171.6489) (9022.916 4165.4198) (9025.771 4159.8015) (9030.229 4155.3435) (9035.8473 4152.4885)
      (9042.0763 4151.4962) (9048.3053 4152.4885) (9053.9237 4155.3435) (9058.3817 4159.8015) (9061.2366 4165.4198)
      (9062.229 4171.6489) (9061.2366 4177.8779) (9058.3817 4183.4962) (9053.9237 4187.9542) (9048.3053 4190.8244)
      (9042.0763 4191.8015) (9035.8473 4190.8244) (9030.229 4187.9542) (9025.771 4183.4962) (9022.916 4177.8779)
    ))
    ; P3102 -- see feature_dimensions_mm.csv
    ("06_ORNAMENT" 1 (
      (9021.9237 4042.0916) (9022.916 4035.8626) (9025.771 4030.2443) (9030.229 4025.7863) (9035.8473 4022.916)
      (9042.0763 4021.9389) (9048.3053 4022.916) (9053.9237 4025.7863) (9058.3817 4030.2443) (9061.2366 4035.8626)
      (9062.229 4042.0916) (9061.2366 4048.3206) (9058.3817 4053.9389) (9053.9237 4058.3969) (9048.3053 4061.2519)
      (9042.0763 4062.2443) (9035.8473 4061.2519) (9030.229 4058.3969) (9025.771 4053.9389) (9022.916 4048.3206)
    ))
    ; P3103 -- see feature_dimensions_mm.csv
    ("06_ORNAMENT" 1 (
      (9039.7863 5148.0763) (9040.9924 5143.542) (9044.3206 5140.229) (9048.855 5139.0076) (9053.3893 5140.229)
      (9056.7023 5143.542) (9057.9237 5148.0763) (9056.7023 5152.6107) (9053.3893 5155.9389) (9048.855 5157.145)
      (9044.3206 5155.9389) (9040.9924 5152.6107)
    ))
    ; P3104 -- see feature_dimensions_mm.csv
    ("06_ORNAMENT" 1 (
      (9039.7863 4851.9084) (9040.9924 4847.374) (9044.3206 4844.0611) (9048.855 4842.8397) (9053.3893 4844.0611)
      (9056.7023 4847.374) (9057.9237 4851.9084) (9056.7023 4856.4427) (9053.3893 4859.771) (9048.855 4860.9771)
      (9044.3206 4859.771) (9040.9924 4856.4427)
    ))
    ; P3105 -- see feature_dimensions_mm.csv
    ("06_ORNAMENT" 1 (
      (9039.7863 4552.6565) (9040.9924 4548.1221) (9044.3206 4544.8092) (9048.855 4543.5878) (9053.3893 4544.8092)
      (9056.7023 4548.1221) (9057.9237 4552.6565) (9056.7023 4557.1908) (9053.3893 4560.5191) (9048.855 4561.7252)
      (9044.3206 4560.5191) (9040.9924 4557.1908)
    ))
    ; P3106 -- see feature_dimensions_mm.csv
    ("06_ORNAMENT" 1 (
      (9039.7863 4256.4885) (9040.9924 4251.9542) (9044.3206 4248.6412) (9048.855 4247.4198) (9053.3893 4248.6412)
      (9056.7023 4251.9542) (9057.9237 4256.4885) (9056.7023 4261.0229) (9053.3893 4264.3511) (9048.855 4265.5573)
      (9044.3206 4264.3511) (9040.9924 4261.0229)
    ))
    ; P3107 -- see feature_dimensions_mm.csv
    ("06_ORNAMENT" 1 (
      (9039.7863 3957.2366) (9040.9924 3952.7176) (9044.3206 3949.3893) (9048.855 3948.1679) (9053.3893 3949.3893)
      (9056.7023 3952.7176) (9057.9237 3957.2366) (9056.7023 3961.771) (9053.3893 3965.0992) (9048.855 3966.3053)
      (9044.3206 3965.0992) (9040.9924 3961.771)
    ))
    ; P3108 -- see feature_dimensions_mm.csv
    ("06_ORNAMENT" 1 (
      (9044.2748 7389.313) (9045.6336 7386.7939) (9049.3435 7384.7481) (9054.3817 7383.4198) (9059.4351 7382.7328)
      (9063.2214 7382.2748) (9064.9008 7381.4198) (9064.3053 7379.6183) (9061.9695 7376.6107) (9058.8855 7372.5496)
      (9056.2595 7368.0458) (9055.084 7363.9847) (9055.9084 7361.2519) (9058.6412 7360.4275) (9062.7023 7361.6031)
      (9067.2061 7364.229) (9071.2672 7367.313) (9074.2748 7369.6489) (9076.0763 7370.2443) (9076.9313 7368.5649)
      (9077.3893 7364.7786) (9078.0916 7359.7252) (9079.4046 7354.687) (9081.4504 7350.9771) (9083.9695 7349.6183)
      (9086.4885 7350.9771) (9088.5344 7354.687) (9089.8626 7359.7252) (9090.5496 7364.7786) (9091.0076 7368.5649)
      (9091.8626 7370.2443) (9093.6641 7369.6489) (9096.6718 7367.313) (9100.7328 7364.229) (9105.2366 7361.6031)
      (9109.2977 7360.4275) (9112.0305 7361.2519) (9112.855 7363.9847) (9111.6794 7368.0458) (9109.0534 7372.5496)
      (9105.9695 7376.6107) (9103.6336 7379.6183) (9103.0382 7381.4198) (9104.7176 7382.2748) (9108.5038 7382.7328)
      (9113.5573 7383.4198) (9118.5954 7384.7481) (9122.3053 7386.7939) (9123.6641 7389.313) (9122.3053 7391.8321)
      (9118.5954 7393.8779) (9113.5573 7395.1908) (9108.5038 7395.8931) (9104.7176 7396.3511) (9103.0382 7397.2061)
      (9103.6336 7399.0076) (9105.9695 7402.0153) (9109.0534 7406.0763) (9111.6794 7410.5802) (9112.855 7414.6412)
      (9112.0305 7417.374) (9109.2977 7418.1985) (9105.2366 7417.0229) (9100.7328 7414.3969) (9096.6718 7411.313)
      (9093.6641 7408.9771) (9091.8626 7408.3817) (9091.0076 7410.0611) (9090.5496 7413.8473) (9089.8626 7418.9008)
      (9088.5344 7423.9389) (9086.4885 7427.6489) (9083.9695 7429.0076) (9081.4504 7427.6489) (9079.4046 7423.9389)
      (9078.0916 7418.9008) (9077.3893 7413.8473) (9076.9313 7410.0611) (9076.0763 7408.3817) (9074.2748 7408.9771)
      (9071.2672 7411.313) (9067.2061 7414.3969) (9062.7023 7417.0229) (9058.6412 7418.1985) (9055.9084 7417.374)
      (9055.084 7414.6412) (9056.2595 7410.5802) (9058.8855 7406.0763) (9061.9695 7402.0153) (9064.3053 7399.0076)
      (9064.9008 7397.2061) (9063.2214 7396.3511) (9059.4351 7395.8931) (9054.3817 7395.1908) (9049.3435 7393.8779)
      (9045.6336 7391.8321)
    ))
    ; P3109 -- see feature_dimensions_mm.csv
    ("06_ORNAMENT" 1 (
      (9044.2748 7206.1069) (9045.6336 7203.5878) (9049.3435 7201.542) (9054.3817 7200.2137) (9059.4351 7199.5267)
      (9063.2214 7199.0687) (9064.9008 7198.2137) (9064.3053 7196.4122) (9061.9695 7193.4046) (9058.8855 7189.3435)
      (9056.2595 7184.8397) (9055.084 7180.7786) (9055.9084 7178.0458) (9058.6412 7177.2214) (9062.7023 7178.3969)
      (9067.2061 7181.0229) (9071.2672 7184.1069) (9074.2748 7186.4427) (9076.0763 7187.0382) (9076.9313 7185.3588)
      (9077.3893 7181.5725) (9078.0916 7176.5191) (9079.4046 7171.4809) (9081.4504 7167.771) (9083.9695 7166.4122)
      (9086.4885 7167.771) (9088.5344 7171.4809) (9089.8626 7176.5191) (9090.5496 7181.5725) (9091.0076 7185.3588)
      (9091.8626 7187.0382) (9093.6641 7186.4427) (9096.6718 7184.1069) (9100.7328 7181.0229) (9105.2366 7178.3969)
      (9109.2977 7177.2214) (9112.0305 7178.0458) (9112.855 7180.7786) (9111.6794 7184.8397) (9109.0534 7189.3435)
      (9105.9695 7193.4046) (9103.6336 7196.4122) (9103.0382 7198.2137) (9104.7176 7199.0687) (9108.5038 7199.5267)
      (9113.5573 7200.2137) (9118.5954 7201.542) (9122.3053 7203.5878) (9123.6641 7206.1069) (9122.3053 7208.626)
      (9118.5954 7210.6718) (9113.5573 7211.9847) (9108.5038 7212.687) (9104.7176 7213.145) (9103.0382 7214.0)
      (9103.6336 7215.8015) (9105.9695 7218.8092) (9109.0534 7222.8702) (9111.6794 7227.374) (9112.855 7231.4351)
      (9112.0305 7234.1679) (9109.2977 7234.9924) (9105.2366 7233.8168) (9100.7328 7231.1908) (9096.6718 7228.1069)
      (9093.6641 7225.771) (9091.8626 7225.1756) (9091.0076 7226.855) (9090.5496 7230.6412) (9089.8626 7235.6947)
      (9088.5344 7240.7328) (9086.4885 7244.4427) (9083.9695 7245.8015) (9081.4504 7244.4427) (9079.4046 7240.7328)
      (9078.0916 7235.6947) (9077.3893 7230.6412) (9076.9313 7226.855) (9076.0763 7225.1756) (9074.2748 7225.771)
      (9071.2672 7228.1069) (9067.2061 7231.1908) (9062.7023 7233.8168) (9058.6412 7234.9924) (9055.9084 7234.1679)
      (9055.084 7231.4351) (9056.2595 7227.374) (9058.8855 7222.8702) (9061.9695 7218.8092) (9064.3053 7215.8015)
      (9064.9008 7214.0) (9063.2214 7213.145) (9059.4351 7212.687) (9054.3817 7211.9847) (9049.3435 7210.6718)
      (9045.6336 7208.626)
    ))
    ; P3110 -- see feature_dimensions_mm.csv
    ("06_ORNAMENT" 1 (
      (9047.3282 5297.7099) (9047.8931 5293.6183) (9049.6031 5289.6183) (9052.3817 5285.8168) (9056.1832 5282.3053)
      (9060.9008 5279.1908) (9066.4275 5276.5191) (9072.6412 5274.3664) (9079.3588 5272.7939) (9086.4275 5271.8321)
      (9093.6794 5271.5115) (9100.9313 5271.8321) (9108.0 5272.7939) (9114.7176 5274.3664) (9120.9313 5276.5191)
      (9126.458 5279.1908) (9131.1756 5282.3053) (9134.9771 5285.8168) (9137.7557 5289.6183) (9139.4656 5293.6183)
      (9140.0305 5297.7099) (9139.4656 5301.8015) (9137.7557 5305.8015) (9134.9771 5309.6031) (9131.1756 5313.1145)
      (9126.458 5316.229) (9120.9313 5318.9008) (9114.7176 5321.0534) (9108.0 5322.626) (9100.9313 5323.5878)
      (9093.6794 5323.9084) (9086.4275 5323.5878) (9079.3588 5322.626) (9072.6412 5321.0534) (9066.4275 5318.9008)
      (9060.9008 5316.229) (9056.1832 5313.1145) (9052.3817 5309.6031) (9049.6031 5305.8015) (9047.8931 5301.8015)
    ))
    ; P3111 -- see feature_dimensions_mm.csv
    ("06_ORNAMENT" 1 (
      (9047.3282 4702.2901) (9047.8931 4698.1985) (9049.6031 4694.1985) (9052.3817 4690.3969) (9056.1832 4686.8855)
      (9060.9008 4683.771) (9066.4275 4681.0992) (9072.6412 4678.9466) (9079.3588 4677.374) (9086.4275 4676.4122)
      (9093.6794 4676.0916) (9100.9313 4676.4122) (9108.0 4677.374) (9114.7176 4678.9466) (9120.9313 4681.0992)
      (9126.458 4683.771) (9131.1756 4686.8855) (9134.9771 4690.3969) (9137.7557 4694.1985) (9139.4656 4698.1985)
      (9140.0305 4702.2901) (9139.4656 4706.3817) (9137.7557 4710.3817) (9134.9771 4714.1832) (9131.1756 4717.6947)
      (9126.458 4720.8092) (9120.9313 4723.4809) (9114.7176 4725.6336) (9108.0 4727.2061) (9100.9313 4728.1679)
      (9093.6794 4728.4885) (9086.4275 4728.1679) (9079.3588 4727.2061) (9072.6412 4725.6336) (9066.4275 4723.4809)
      (9060.9008 4720.8092) (9056.1832 4717.6947) (9052.3817 4714.1832) (9049.6031 4710.3817) (9047.8931 4706.3817)
    ))
    ; P3112 -- see feature_dimensions_mm.csv
    ("06_ORNAMENT" 1 (
      (9047.3282 4106.8702) (9047.8931 4102.7786) (9049.6031 4098.7786) (9052.3817 4094.9771) (9056.1832 4091.4656)
      (9060.9008 4088.3511) (9066.4275 4085.6794) (9072.6412 4083.5267) (9079.3588 4081.9542) (9086.4275 4080.9924)
      (9093.6794 4080.6718) (9100.9313 4080.9924) (9108.0 4081.9542) (9114.7176 4083.5267) (9120.9313 4085.6794)
      (9126.458 4088.3511) (9131.1756 4091.4656) (9134.9771 4094.9771) (9137.7557 4098.7786) (9139.4656 4102.7786)
      (9140.0305 4106.8702) (9139.4656 4110.9618) (9137.7557 4114.9618) (9134.9771 4118.7634) (9131.1756 4122.2748)
      (9126.458 4125.3893) (9120.9313 4128.0611) (9114.7176 4130.2137) (9108.0 4131.7863) (9100.9313 4132.7481)
      (9093.6794 4133.0687) (9086.4275 4132.7481) (9079.3588 4131.7863) (9072.6412 4130.2137) (9066.4275 4128.0611)
      (9060.9008 4125.3893) (9056.1832 4122.2748) (9052.3817 4118.7634) (9049.6031 4114.9618) (9047.8931 4110.9618)
    ))
    ; P3113 -- see feature_dimensions_mm.csv
    ("06_ORNAMENT" 1 (
      (9074.8397 7389.313) (9075.542 7385.8168) (9077.5115 7382.855) (9080.4733 7380.8855) (9083.9695 7380.1832)
      (9087.4656 7380.8855) (9090.4275 7382.855) (9092.3969 7385.8168) (9093.0992 7389.313) (9092.3969 7392.8092)
      (9090.4275 7395.771) (9087.4656 7397.7405) (9083.9695 7398.4427) (9080.4733 7397.7405) (9077.5115 7395.771)
      (9075.542 7392.8092)
    ))
    ; P3114 -- see feature_dimensions_mm.csv
    ("06_ORNAMENT" 1 (
      (9074.8397 7206.1069) (9075.542 7202.6107) (9077.5115 7199.6489) (9080.4733 7197.6794) (9083.9695 7196.9771)
      (9087.4656 7197.6794) (9090.4275 7199.6489) (9092.3969 7202.6107) (9093.0992 7206.1069) (9092.3969 7209.6031)
      (9090.4275 7212.5649) (9087.4656 7214.5344) (9083.9695 7215.2366) (9080.4733 7214.5344) (9077.5115 7212.5649)
      (9075.542 7209.6031)
    ))
    ; P3115 -- see feature_dimensions_mm.csv
    ("06_ORNAMENT" 1 (
      (9086.7634 5202.8092) (9087.4809 5198.1679) (9089.0992 5194.1374) (9091.6031 5190.8397) (9094.9008 5188.3359)
      (9098.9313 5186.7176) (9103.5878 5186.0) (9108.7481 5186.1985) (9114.2901 5187.3282) (9120.0916 5189.3588)
      (9126.0 5192.229) (9131.8626 5195.8626) (9137.542 5200.1832) (9142.9008 5205.084) (9147.8015 5210.4427)
      (9152.1221 5216.1221) (9155.7557 5221.9847) (9158.626 5227.8931) (9160.6412 5233.6794) (9161.771 5239.2366)
      (9161.9847 5244.3969) (9161.2672 5249.0534) (9159.6489 5253.084) (9157.145 5256.3817) (9153.8473 5258.8855)
      (9149.8168 5260.5038) (9145.1603 5261.2214) (9140.0 5261.0076) (9134.4427 5259.8779) (9128.6565 5257.8626)
      (9122.7481 5254.9924) (9116.8855 5251.3588) (9111.2061 5247.0382) (9105.8473 5242.1374) (9100.9466 5236.7786)
      (9096.626 5231.0992) (9092.9924 5225.2366) (9090.1221 5219.3282) (9088.0916 5213.5267) (9086.9618 5207.9847)
    ))
    ; P3116 -- see feature_dimensions_mm.csv
    ("06_ORNAMENT" 1 (
      (9086.7634 4797.1756) (9086.9618 4792.0153) (9088.0916 4786.4733) (9090.1221 4780.6718) (9092.9924 4774.7634)
      (9096.626 4768.9008) (9100.9466 4763.2214) (9105.8473 4757.8626) (9111.2061 4752.9618) (9116.8855 4748.6412)
      (9122.7481 4745.0076) (9128.6565 4742.1374) (9134.4427 4740.1221) (9140.0 4738.9924) (9145.1603 4738.7786)
      (9149.8168 4739.4962) (9153.8473 4741.1145) (9157.145 4743.6183) (9159.6489 4746.916) (9161.2672 4750.9466)
      (9161.9847 4755.6031) (9161.771 4760.7634) (9160.6412 4766.3206) (9158.626 4772.1069) (9155.7557 4778.0153)
      (9152.1221 4783.8779) (9147.8015 4789.5573) (9142.9008 4794.916) (9137.542 4799.8168) (9131.8626 4804.1374)
      (9126.0 4807.771) (9120.0916 4810.6412) (9114.2901 4812.6718) (9108.7481 4813.8015) (9103.5878 4814.0)
      (9098.9313 4813.2824) (9094.9008 4811.6641) (9091.6031 4809.1603) (9089.0992 4805.8626) (9087.4809 4801.8321)
    ))
    ; P3117 -- see feature_dimensions_mm.csv
    ("06_ORNAMENT" 1 (
      (9086.7634 4607.3893) (9087.4809 4602.7481) (9089.0992 4598.7176) (9091.6031 4595.4198) (9094.9008 4592.916)
      (9098.9313 4591.2977) (9103.5878 4590.5802) (9108.7481 4590.7786) (9114.2901 4591.9084) (9120.0916 4593.9389)
      (9126.0 4596.8092) (9131.8626 4600.4427) (9137.542 4604.7634) (9142.9008 4609.6641) (9147.8015 4615.0229)
      (9152.1221 4620.7023) (9155.7557 4626.5649) (9158.626 4632.4733) (9160.6412 4638.2595) (9161.771 4643.8168)
      (9161.9847 4648.9771) (9161.2672 4653.6336) (9159.6489 4657.6641) (9157.145 4660.9618) (9153.8473 4663.4656)
      (9149.8168 4665.084) (9145.1603 4665.8015) (9140.0 4665.5878) (9134.4427 4664.458) (9128.6565 4662.4427)
      (9122.7481 4659.5725) (9116.8855 4655.9389) (9111.2061 4651.6183) (9105.8473 4646.7176) (9100.9466 4641.3588)
      (9096.626 4635.6794) (9092.9924 4629.8168) (9090.1221 4623.9084) (9088.0916 4618.1069) (9086.9618 4612.5649)
    ))
    ; P3118 -- see feature_dimensions_mm.csv
    ("06_ORNAMENT" 1 (
      (9086.7634 4201.7557) (9086.9618 4196.5954) (9088.0916 4191.0534) (9090.1221 4185.2519) (9092.9924 4179.3435)
      (9096.626 4173.4809) (9100.9466 4167.8015) (9105.8473 4162.4427) (9111.2061 4157.542) (9116.8855 4153.2214)
      (9122.7481 4149.5878) (9128.6565 4146.7176) (9134.4427 4144.7023) (9140.0 4143.5725) (9145.1603 4143.3588)
      (9149.8168 4144.0763) (9153.8473 4145.6947) (9157.145 4148.1985) (9159.6489 4151.4962) (9161.2672 4155.5267)
      (9161.9847 4160.1832) (9161.771 4165.3435) (9160.6412 4170.9008) (9158.626 4176.687) (9155.7557 4182.5954)
      (9152.1221 4188.458) (9147.8015 4194.1374) (9142.9008 4199.4962) (9137.542 4204.3969) (9131.8626 4208.7176)
      (9126.0 4212.3511) (9120.0916 4215.2214) (9114.2901 4217.2519) (9108.7481 4218.3817) (9103.5878 4218.5802)
      (9098.9313 4217.8626) (9094.9008 4216.2443) (9091.6031 4213.7405) (9089.0992 4210.4427) (9087.4809 4206.4122)
    ))
    ; P3119 -- see feature_dimensions_mm.csv
    ("06_ORNAMENT" 1 (
      (9086.7634 4011.9695) (9087.4809 4007.3282) (9089.0992 4003.2977) (9091.6031 4000.0) (9094.9008 3997.4962)
      (9098.9313 3995.8779) (9103.5878 3995.1603) (9108.7481 3995.3588) (9114.2901 3996.4885) (9120.0916 3998.5191)
      (9126.0 4001.3893) (9131.8626 4005.0229) (9137.542 4009.3435) (9142.9008 4014.2443) (9147.8015 4019.6031)
      (9152.1221 4025.2824) (9155.7557 4031.145) (9158.626 4037.0534) (9160.6412 4042.8397) (9161.771 4048.3969)
      (9161.9847 4053.5573) (9161.2672 4058.2137) (9159.6489 4062.2443) (9157.145 4065.542) (9153.8473 4068.0458)
      (9149.8168 4069.6641) (9145.1603 4070.3817) (9140.0 4070.1679) (9134.4427 4069.0382) (9128.6565 4067.0229)
      (9122.7481 4064.1527) (9116.8855 4060.5191) (9111.2061 4056.1985) (9105.8473 4051.2977) (9100.9466 4045.9389)
      (9096.626 4040.2595) (9092.9924 4034.3969) (9090.1221 4028.4885) (9088.0916 4022.687) (9086.9618 4017.145)
    ))
    ; P3120 -- see feature_dimensions_mm.csv
    ("06_ORNAMENT" 1 (
      (9108.4275 5102.2137) (9109.6489 5097.6794) (9112.9618 5094.3664) (9117.4962 5093.145) (9122.0305 5094.3664)
      (9125.3435 5097.6794) (9126.5649 5102.2137) (9125.3435 5106.7481) (9122.0305 5110.0611) (9117.4962 5111.2824)
      (9112.9618 5110.0611) (9109.6489 5106.7481)
    ))
    ; P3121 -- see feature_dimensions_mm.csv
    ("06_ORNAMENT" 1 (
      (9108.4275 4897.7863) (9109.6489 4893.2519) (9112.9618 4889.9389) (9117.4962 4888.7176) (9122.0305 4889.9389)
      (9125.3435 4893.2519) (9126.5649 4897.7863) (9125.3435 4902.3206) (9122.0305 4905.6336) (9117.4962 4906.855)
      (9112.9618 4905.6336) (9109.6489 4902.3206)
    ))
    ; P3122 -- see feature_dimensions_mm.csv
    ("06_ORNAMENT" 1 (
      (9108.4275 4506.7939) (9109.6489 4502.2595) (9112.9618 4498.9466) (9117.4962 4497.7252) (9122.0305 4498.9466)
      (9125.3435 4502.2595) (9126.5649 4506.7939) (9125.3435 4511.3282) (9122.0305 4514.6412) (9117.4962 4515.8626)
      (9112.9618 4514.6412) (9109.6489 4511.3282)
    ))
    ; P3123 -- see feature_dimensions_mm.csv
    ("06_ORNAMENT" 1 (
      (9108.4275 4302.3664) (9109.6489 4297.8321) (9112.9618 4294.5191) (9117.4962 4293.2977) (9122.0305 4294.5191)
      (9125.3435 4297.8321) (9126.5649 4302.3664) (9125.3435 4306.9008) (9122.0305 4310.2137) (9117.4962 4311.4351)
      (9112.9618 4310.2137) (9109.6489 4306.9008)
    ))
    ; P3124 -- see feature_dimensions_mm.csv
    ("06_ORNAMENT" 1 (
      (9108.4275 3911.374) (9109.6489 3906.8397) (9112.9618 3903.5267) (9117.4962 3902.3053) (9122.0305 3903.5267)
      (9125.3435 3906.8397) (9126.5649 3911.374) (9125.3435 3915.9084) (9122.0305 3919.2214) (9117.4962 3920.4427)
      (9112.9618 3919.2214) (9109.6489 3915.9084)
    ))
    ; P3125 -- see feature_dimensions_mm.csv
    ("06_ORNAMENT" 1 (
      (9113.542 5141.313) (9114.5191 5135.084) (9117.3893 5129.4656) (9121.8473 5125.0076) (9127.4656 5122.1527)
      (9133.6947 5121.1603) (9139.9237 5122.1527) (9145.542 5125.0076) (9150.0 5129.4656) (9152.855 5135.084)
      (9153.8473 5141.313) (9152.855 5147.542) (9150.0 5153.1603) (9145.542 5157.6183) (9139.9237 5160.4733)
      (9133.6947 5161.4656) (9127.4656 5160.4733) (9121.8473 5157.6183) (9117.3893 5153.1603) (9114.5191 5147.542)
    ))
    ; P3126 -- see feature_dimensions_mm.csv
    ("06_ORNAMENT" 1 (
      (9113.542 4858.687) (9114.5191 4852.458) (9117.3893 4846.8397) (9121.8473 4842.3817) (9127.4656 4839.5267)
      (9133.6947 4838.5344) (9139.9237 4839.5267) (9145.542 4842.3817) (9150.0 4846.8397) (9152.855 4852.458)
      (9153.8473 4858.687) (9152.855 4864.916) (9150.0 4870.5344) (9145.542 4874.9924) (9139.9237 4877.8473)
      (9133.6947 4878.8397) (9127.4656 4877.8473) (9121.8473 4874.9924) (9117.3893 4870.5344) (9114.5191 4864.916)
    ))
    ; P3127 -- see feature_dimensions_mm.csv
    ("06_ORNAMENT" 1 (
      (9113.542 4545.8931) (9114.5191 4539.6641) (9117.3893 4534.0458) (9121.8473 4529.5878) (9127.4656 4526.7328)
      (9133.6947 4525.7405) (9139.9237 4526.7328) (9145.542 4529.5878) (9150.0 4534.0458) (9152.855 4539.6641)
      (9153.8473 4545.8931) (9152.855 4552.1221) (9150.0 4557.7405) (9145.542 4562.1985) (9139.9237 4565.0534)
      (9133.6947 4566.0458) (9127.4656 4565.0534) (9121.8473 4562.1985) (9117.3893 4557.7405) (9114.5191 4552.1221)
    ))
    ; P3128 -- see feature_dimensions_mm.csv
    ("06_ORNAMENT" 1 (
      (9113.542 4263.2672) (9114.5191 4257.0382) (9117.3893 4251.4198) (9121.8473 4246.9618) (9127.4656 4244.1069)
      (9133.6947 4243.1145) (9139.9237 4244.1069) (9145.542 4246.9618) (9150.0 4251.4198) (9152.855 4257.0382)
      (9153.8473 4263.2672) (9152.855 4269.4962) (9150.0 4275.1145) (9145.542 4279.5725) (9139.9237 4282.4275)
      (9133.6947 4283.4198) (9127.4656 4282.4275) (9121.8473 4279.5725) (9117.3893 4275.1145) (9114.5191 4269.4962)
    ))
    ; P3129 -- see feature_dimensions_mm.csv
    ("06_ORNAMENT" 1 (
      (9113.542 3950.4733) (9114.5191 3944.2443) (9117.3893 3938.626) (9121.8473 3934.1679) (9127.4656 3931.313)
      (9133.6947 3930.3206) (9139.9237 3931.313) (9145.542 3934.1679) (9150.0 3938.626) (9152.855 3944.2443)
      (9153.8473 3950.4733) (9152.855 3956.7023) (9150.0 3962.3206) (9145.542 3966.7786) (9139.9237 3969.6336)
      (9133.6947 3970.626) (9127.4656 3969.6336) (9121.8473 3966.7786) (9117.3893 3962.3206) (9114.5191 3956.7023)
    ))
    ; P3130 -- see feature_dimensions_mm.csv
    ("06_ORNAMENT" 1 (
      (9150.1069 5297.7099) (9151.0382 5288.2748) (9153.7863 5279.2061) (9158.2595 5270.8397) (9164.2748 5263.5115)
      (9171.6031 5257.4962) (9179.9695 5253.0229) (9189.0382 5250.2748) (9198.4733 5249.3435) (9207.9084 5250.2748)
      (9216.9771 5253.0229) (9225.3435 5257.4962) (9232.6718 5263.5115) (9238.687 5270.8397) (9243.1603 5279.2061)
      (9245.9084 5288.2748) (9246.8397 5297.7099) (9245.9084 5307.145) (9243.1603 5316.2137) (9238.687 5324.5802)
      (9232.6718 5331.9084) (9225.3435 5337.9237) (9216.9771 5342.3969) (9207.9084 5345.145) (9198.4733 5346.0763)
      (9189.0382 5345.145) (9179.9695 5342.3969) (9171.6031 5337.9237) (9164.2748 5331.9084) (9158.2595 5324.5802)
      (9153.7863 5316.2137) (9151.0382 5307.145)
    ))
    ; P3131 -- see feature_dimensions_mm.csv
    ("06_ORNAMENT" 1 (
      (9150.1069 4702.2901) (9151.0382 4692.855) (9153.7863 4683.7863) (9158.2595 4675.4198) (9164.2748 4668.0916)
      (9171.6031 4662.0763) (9179.9695 4657.6031) (9189.0382 4654.855) (9198.4733 4653.9237) (9207.9084 4654.855)
      (9216.9771 4657.6031) (9225.3435 4662.0763) (9232.6718 4668.0916) (9238.687 4675.4198) (9243.1603 4683.7863)
      (9245.9084 4692.855) (9246.8397 4702.2901) (9245.9084 4711.7252) (9243.1603 4720.7939) (9238.687 4729.1603)
      (9232.6718 4736.4885) (9225.3435 4742.5038) (9216.9771 4746.9771) (9207.9084 4749.7252) (9198.4733 4750.6565)
      (9189.0382 4749.7252) (9179.9695 4746.9771) (9171.6031 4742.5038) (9164.2748 4736.4885) (9158.2595 4729.1603)
      (9153.7863 4720.7939) (9151.0382 4711.7252)
    ))
    ; P3132 -- see feature_dimensions_mm.csv
    ("06_ORNAMENT" 1 (
      (9150.1069 4106.8702) (9151.0382 4097.4351) (9153.7863 4088.3664) (9158.2595 4080.0) (9164.2748 4072.6718)
      (9171.6031 4066.6565) (9179.9695 4062.1832) (9189.0382 4059.4351) (9198.4733 4058.5038) (9207.9084 4059.4351)
      (9216.9771 4062.1832) (9225.3435 4066.6565) (9232.6718 4072.6718) (9238.687 4080.0) (9243.1603 4088.3664)
      (9245.9084 4097.4351) (9246.8397 4106.8702) (9245.9084 4116.3053) (9243.1603 4125.374) (9238.687 4133.7405)
      (9232.6718 4141.0687) (9225.3435 4147.084) (9216.9771 4151.5573) (9207.9084 4154.3053) (9198.4733 4155.2366)
      (9189.0382 4154.3053) (9179.9695 4151.5573) (9171.6031 4147.084) (9164.2748 4141.0687) (9158.2595 4133.7405)
      (9153.7863 4125.374) (9151.0382 4116.3053)
    ))
    ; P3133 -- see feature_dimensions_mm.csv
    ("06_ORNAMENT" 1 (
      (9158.7786 5007.6336) (9159.1908 5005.0534) (9160.3817 5002.626) (9162.2748 5000.4275) (9164.7328 4998.5954)
      (9167.5725 4997.145) (9170.5954 4996.0916) (9173.6336 4995.374) (9176.4733 4994.9313) (9178.9924 4994.6107)
      (9181.084 4994.2901) (9182.7176 4993.8168) (9183.8779 4993.0382) (9184.6565 4991.8779) (9185.1298 4990.2443)
      (9185.4504 4988.1527) (9185.771 4985.6336) (9186.2137 4982.7939) (9186.9313 4979.7557) (9187.9847 4976.7328)
      (9189.4351 4973.8931) (9191.2672 4971.4351) (9193.4656 4969.542) (9195.8931 4968.3511) (9198.4733 4967.9389)
      (9201.0534 4968.3511) (9203.4809 4969.542) (9205.6794 4971.4351) (9207.5115 4973.8931) (9208.9618 4976.7328)
      (9210.0153 4979.7557) (9210.7328 4982.7939) (9211.1756 4985.6336) (9211.4962 4988.1527) (9211.8168 4990.2443)
      (9212.2901 4991.8779) (9213.0687 4993.0382) (9214.229 4993.8168) (9215.8626 4994.2901) (9217.9542 4994.6107)
      (9220.4733 4994.9313) (9223.313 4995.374) (9226.3511 4996.0916) (9229.374 4997.145) (9232.2137 4998.5954)
      (9234.6718 5000.4275) (9236.5649 5002.626) (9237.7557 5005.0534) (9238.1679 5007.6336) (9237.7557 5010.2137)
      (9236.5649 5012.6412) (9234.6718 5014.8397) (9232.2137 5016.6718) (9229.374 5018.1221) (9226.3511 5019.1756)
      (9223.313 5019.8931) (9220.4733 5020.3359) (9217.9542 5020.6565) (9215.8626 5020.9771) (9214.229 5021.4504)
      (9213.0687 5022.229) (9212.2901 5023.3893) (9211.8168 5025.0229) (9211.4962 5027.1145) (9211.1756 5029.6336)
      (9210.7328 5032.4733) (9210.0153 5035.5115) (9208.9618 5038.5344) (9207.5115 5041.374) (9205.6794 5043.8321)
      (9203.4809 5045.7252) (9201.0534 5046.916) (9198.4733 5047.3282) (9195.8931 5046.916) (9193.4656 5045.7252)
      (9191.2672 5043.8321) (9189.4351 5041.374) (9187.9847 5038.5344) (9186.9313 5035.5115) (9186.2137 5032.4733)
      (9185.771 5029.6336) (9185.4504 5027.1145) (9185.1298 5025.0229) (9184.6565 5023.3893) (9183.8779 5022.229)
      (9182.7176 5021.4504) (9181.084 5020.9771) (9178.9924 5020.6565) (9176.4733 5020.3359) (9173.6336 5019.8931)
      (9170.5954 5019.1756) (9167.5725 5018.1221) (9164.7328 5016.6718) (9162.2748 5014.8397) (9160.3817 5012.6412)
      (9159.1908 5010.2137)
    ))
    ; P3134 -- see feature_dimensions_mm.csv
    ("06_ORNAMENT" 1 (
      (9170.2595 5297.7099) (9171.2214 5290.4122) (9174.0458 5283.6031) (9178.5191 5277.7557) (9184.3664 5273.2824)
      (9191.1756 5270.458) (9198.4733 5269.4962) (9205.771 5270.458) (9212.5802 5273.2824) (9218.4275 5277.7557)
      (9222.9008 5283.6031) (9225.7252 5290.4122) (9226.687 5297.7099) (9225.7252 5305.0076) (9222.9008 5311.8168)
      (9218.4275 5317.6641) (9212.5802 5322.1374) (9205.771 5324.9618) (9198.4733 5325.9237) (9191.1756 5324.9618)
      (9184.3664 5322.1374) (9178.5191 5317.6641) (9174.0458 5311.8168) (9171.2214 5305.0076)
    ))
    ; P3135 -- see feature_dimensions_mm.csv
    ("06_ORNAMENT" 1 (
      (9170.2595 4702.2901) (9171.2214 4694.9924) (9174.0458 4688.1832) (9178.5191 4682.3359) (9184.3664 4677.8626)
      (9191.1756 4675.0382) (9198.4733 4674.0763) (9205.771 4675.0382) (9212.5802 4677.8626) (9218.4275 4682.3359)
      (9222.9008 4688.1832) (9225.7252 4694.9924) (9226.687 4702.2901) (9225.7252 4709.5878) (9222.9008 4716.3969)
      (9218.4275 4722.2443) (9212.5802 4726.7176) (9205.771 4729.542) (9198.4733 4730.5038) (9191.1756 4729.542)
      (9184.3664 4726.7176) (9178.5191 4722.2443) (9174.0458 4716.3969) (9171.2214 4709.5878)
    ))
    ; P3136 -- see feature_dimensions_mm.csv
    ("06_ORNAMENT" 1 (
      (9170.2595 4106.8702) (9171.2214 4099.5725) (9174.0458 4092.7634) (9178.5191 4086.916) (9184.3664 4082.4427)
      (9191.1756 4079.6183) (9198.4733 4078.6565) (9205.771 4079.6183) (9212.5802 4082.4427) (9218.4275 4086.916)
      (9222.9008 4092.7634) (9225.7252 4099.5725) (9226.687 4106.8702) (9225.7252 4114.1679) (9222.9008 4120.9771)
      (9218.4275 4126.8244) (9212.5802 4131.2977) (9205.771 4134.1221) (9198.4733 4135.084) (9191.1756 4134.1221)
      (9184.3664 4131.2977) (9178.5191 4126.8244) (9174.0458 4120.9771) (9171.2214 4114.1679)
    ))
    ; P3137 -- see feature_dimensions_mm.csv
    ("06_ORNAMENT" 1 (
      (9172.2748 5192.916) (9172.5954 5185.6641) (9173.5573 5178.5954) (9175.1298 5171.8779) (9177.2824 5165.6641)
      (9179.9542 5160.1374) (9183.0687 5155.4198) (9186.5802 5151.6183) (9190.3817 5148.8397) (9194.3817 5147.1298)
      (9198.4733 5146.5649) (9202.5649 5147.1298) (9206.5649 5148.8397) (9210.3664 5151.6183) (9213.8779 5155.4198)
      (9216.9924 5160.1374) (9219.6641 5165.6641) (9221.8168 5171.8779) (9223.3893 5178.5954) (9224.3511 5185.6641)
      (9224.6718 5192.916) (9224.3511 5200.1679) (9223.3893 5207.2366) (9221.8168 5213.9542) (9219.6641 5220.1679)
      (9216.9924 5225.6947) (9213.8779 5230.4122) (9210.3664 5234.2137) (9206.5649 5236.9924) (9202.5649 5238.7023)
      (9198.4733 5239.2672) (9194.3817 5238.7023) (9190.3817 5236.9924) (9186.5802 5234.2137) (9183.0687 5230.4122)
      (9179.9542 5225.6947) (9177.2824 5220.1679) (9175.1298 5213.9542) (9173.5573 5207.2366) (9172.5954 5200.1679)
    ))
    ; P3138 -- see feature_dimensions_mm.csv
    ("06_ORNAMENT" 1 (
      (9172.2748 4807.084) (9172.5954 4799.8321) (9173.5573 4792.7634) (9175.1298 4786.0458) (9177.2824 4779.8321)
      (9179.9542 4774.3053) (9183.0687 4769.5878) (9186.5802 4765.7863) (9190.3817 4763.0076) (9194.3817 4761.2977)
      (9198.4733 4760.7328) (9202.5649 4761.2977) (9206.5649 4763.0076) (9210.3664 4765.7863) (9213.8779 4769.5878)
      (9216.9924 4774.3053) (9219.6641 4779.8321) (9221.8168 4786.0458) (9223.3893 4792.7634) (9224.3511 4799.8321)
      (9224.6718 4807.084) (9224.3511 4814.3359) (9223.3893 4821.4046) (9221.8168 4828.1221) (9219.6641 4834.3359)
      (9216.9924 4839.8626) (9213.8779 4844.5802) (9210.3664 4848.3817) (9206.5649 4851.1603) (9202.5649 4852.8702)
      (9198.4733 4853.4351) (9194.3817 4852.8702) (9190.3817 4851.1603) (9186.5802 4848.3817) (9183.0687 4844.5802)
      (9179.9542 4839.8626) (9177.2824 4834.3359) (9175.1298 4828.1221) (9173.5573 4821.4046) (9172.5954 4814.3359)
    ))
    ; P3139 -- see feature_dimensions_mm.csv
    ("06_ORNAMENT" 1 (
      (9172.2748 4597.4962) (9172.5954 4590.2443) (9173.5573 4583.1756) (9175.1298 4576.458) (9177.2824 4570.2443)
      (9179.9542 4564.7176) (9183.0687 4560.0) (9186.5802 4556.1985) (9190.3817 4553.4198) (9194.3817 4551.7099)
      (9198.4733 4551.145) (9202.5649 4551.7099) (9206.5649 4553.4198) (9210.3664 4556.1985) (9213.8779 4560.0)
      (9216.9924 4564.7176) (9219.6641 4570.2443) (9221.8168 4576.458) (9223.3893 4583.1756) (9224.3511 4590.2443)
      (9224.6718 4597.4962) (9224.3511 4604.7481) (9223.3893 4611.8168) (9221.8168 4618.5344) (9219.6641 4624.7481)
      (9216.9924 4630.2748) (9213.8779 4634.9924) (9210.3664 4638.7939) (9206.5649 4641.5725) (9202.5649 4643.2824)
      (9198.4733 4643.8473) (9194.3817 4643.2824) (9190.3817 4641.5725) (9186.5802 4638.7939) (9183.0687 4634.9924)
      (9179.9542 4630.2748) (9177.2824 4624.7481) (9175.1298 4618.5344) (9173.5573 4611.8168) (9172.5954 4604.7481)
    ))
    ; P3140 -- see feature_dimensions_mm.csv
    ("06_ORNAMENT" 1 (
      (9172.2748 4211.6641) (9172.5954 4204.4122) (9173.5573 4197.3435) (9175.1298 4190.626) (9177.2824 4184.4122)
      (9179.9542 4178.8855) (9183.0687 4174.1679) (9186.5802 4170.3664) (9190.3817 4167.5878) (9194.3817 4165.8779)
      (9198.4733 4165.313) (9202.5649 4165.8779) (9206.5649 4167.5878) (9210.3664 4170.3664) (9213.8779 4174.1679)
      (9216.9924 4178.8855) (9219.6641 4184.4122) (9221.8168 4190.626) (9223.3893 4197.3435) (9224.3511 4204.4122)
      (9224.6718 4211.6641) (9224.3511 4218.916) (9223.3893 4225.9847) (9221.8168 4232.7023) (9219.6641 4238.916)
      (9216.9924 4244.4427) (9213.8779 4249.1603) (9210.3664 4252.9618) (9206.5649 4255.7405) (9202.5649 4257.4504)
      (9198.4733 4258.0153) (9194.3817 4257.4504) (9190.3817 4255.7405) (9186.5802 4252.9618) (9183.0687 4249.1603)
      (9179.9542 4244.4427) (9177.2824 4238.916) (9175.1298 4232.7023) (9173.5573 4225.9847) (9172.5954 4218.916)
    ))
    ; P3141 -- see feature_dimensions_mm.csv
    ("06_ORNAMENT" 1 (
      (9172.2748 4002.0763) (9172.5954 3994.8244) (9173.5573 3987.7557) (9175.1298 3981.0382) (9177.2824 3974.8244)
      (9179.9542 3969.2977) (9183.0687 3964.5802) (9186.5802 3960.7786) (9190.3817 3958.0) (9194.3817 3956.2901)
      (9198.4733 3955.7252) (9202.5649 3956.2901) (9206.5649 3958.0) (9210.3664 3960.7786) (9213.8779 3964.5802)
      (9216.9924 3969.2977) (9219.6641 3974.8244) (9221.8168 3981.0382) (9223.3893 3987.7557) (9224.3511 3994.8244)
      (9224.6718 4002.0763) (9224.3511 4009.3282) (9223.3893 4016.3969) (9221.8168 4023.1145) (9219.6641 4029.3282)
      (9216.9924 4034.855) (9213.8779 4039.5725) (9210.3664 4043.374) (9206.5649 4046.1527) (9202.5649 4047.8626)
      (9198.4733 4048.4275) (9194.3817 4047.8626) (9190.3817 4046.1527) (9186.5802 4043.374) (9183.0687 4039.5725)
      (9179.9542 4034.855) (9177.2824 4029.3282) (9175.1298 4023.1145) (9173.5573 4016.3969) (9172.5954 4009.3282)
    ))
    ; P3142 -- see feature_dimensions_mm.csv
    ("06_ORNAMENT" 1 (
      (9189.4046 5086.1069) (9190.626 5081.5725) (9193.9389 5078.2595) (9198.4733 5077.0382) (9203.0076 5078.2595)
      (9206.3206 5081.5725) (9207.542 5086.1069) (9206.3206 5090.6412) (9203.0076 5093.9542) (9198.4733 5095.1756)
      (9193.9389 5093.9542) (9190.626 5090.6412)
    ))
    ; P3143 -- see feature_dimensions_mm.csv
    ("06_ORNAMENT" 1 (
      (9189.4046 4913.8931) (9190.626 4909.3588) (9193.9389 4906.0458) (9198.4733 4904.8244) (9203.0076 4906.0458)
      (9206.3206 4909.3588) (9207.542 4913.8931) (9206.3206 4918.4275) (9203.0076 4921.7405) (9198.4733 4922.9618)
      (9193.9389 4921.7405) (9190.626 4918.4275)
    ))
    ; P3144 -- see feature_dimensions_mm.csv
    ("06_ORNAMENT" 1 (
      (9189.4046 4490.687) (9190.626 4486.1527) (9193.9389 4482.8397) (9198.4733 4481.6183) (9203.0076 4482.8397)
      (9206.3206 4486.1527) (9207.542 4490.687) (9206.3206 4495.2214) (9203.0076 4498.5344) (9198.4733 4499.7557)
      (9193.9389 4498.5344) (9190.626 4495.2214)
    ))
    ; P3145 -- see feature_dimensions_mm.csv
    ("06_ORNAMENT" 1 (
      (9189.4046 4318.4733) (9190.626 4313.9389) (9193.9389 4310.626) (9198.4733 4309.4046) (9203.0076 4310.626)
      (9206.3206 4313.9389) (9207.542 4318.4733) (9206.3206 4323.0076) (9203.0076 4326.3206) (9198.4733 4327.542)
      (9193.9389 4326.3206) (9190.626 4323.0076)
    ))
    ; P3146 -- see feature_dimensions_mm.csv
    ("06_ORNAMENT" 1 (
      (9189.4046 3895.2672) (9190.626 3890.7328) (9193.9389 3887.4198) (9198.4733 3886.1985) (9203.0076 3887.4198)
      (9206.3206 3890.7328) (9207.542 3895.2672) (9206.3206 3899.8015) (9203.0076 3903.1145) (9198.4733 3904.3359)
      (9193.9389 3903.1145) (9190.626 3899.8015)
    ))
    ; P3147 -- see feature_dimensions_mm.csv
    ("06_ORNAMENT" 1 (
      (9234.9618 5351.0229) (9235.6794 5346.3664) (9237.2977 5342.3359) (9239.8015 5339.0382) (9243.0992 5336.5344)
      (9247.1298 5334.916) (9251.7863 5334.1985) (9256.9466 5334.4122) (9262.5038 5335.542) (9268.2901 5337.5573)
      (9274.1985 5340.4275) (9280.0611 5344.0611) (9285.7405 5348.3817) (9291.0992 5353.2824) (9296.0 5358.6412)
      (9300.3206 5364.3206) (9303.9542 5370.1832) (9306.8244 5376.0916) (9308.855 5381.8931) (9309.9847 5387.4351)
      (9310.1832 5392.5954) (9309.4656 5397.2519) (9307.8473 5401.2824) (9305.3435 5404.5802) (9302.0458 5407.084)
      (9298.0153 5408.7023) (9293.374 5409.4198) (9288.1985 5409.2214) (9282.6565 5408.0916) (9276.855 5406.0611)
      (9270.9466 5403.1908) (9265.084 5399.5573) (9259.4046 5395.2366) (9254.0458 5390.3359) (9249.145 5384.9771)
      (9244.8244 5379.2977) (9241.1908 5373.4351) (9238.3206 5367.5267) (9236.3053 5361.7405) (9235.1756 5356.1832)
    ))
    ; P3148 -- see feature_dimensions_mm.csv
    ("06_ORNAMENT" 1 (
      (9234.9618 5244.3969) (9235.1756 5239.2366) (9236.3053 5233.6794) (9238.3206 5227.8931) (9241.1908 5221.9847)
      (9244.8244 5216.1221) (9249.145 5210.4427) (9254.0458 5205.084) (9259.4046 5200.1832) (9265.084 5195.8626)
      (9270.9466 5192.229) (9276.855 5189.3588) (9282.6565 5187.3282) (9288.1985 5186.1985) (9293.374 5186.0)
      (9298.0153 5186.7176) (9302.0458 5188.3359) (9305.3435 5190.8397) (9307.8473 5194.1374) (9309.4656 5198.1679)
      (9310.1832 5202.8092) (9309.9847 5207.9847) (9308.855 5213.5267) (9306.8244 5219.3282) (9303.9542 5225.2366)
      (9300.3206 5231.0992) (9296.0 5236.7786) (9291.0992 5242.1374) (9285.7405 5247.0382) (9280.0611 5251.3588)
      (9274.1985 5254.9924) (9268.2901 5257.8626) (9262.5038 5259.8779) (9256.9466 5261.0076) (9251.7863 5261.2214)
      (9247.1298 5260.5038) (9243.0992 5258.8855) (9239.8015 5256.3817) (9237.2977 5253.084) (9235.6794 5249.0534)
    ))
    ; P3149 -- see feature_dimensions_mm.csv
    ("06_ORNAMENT" 1 (
      (9234.9618 4755.6031) (9235.6794 4750.9466) (9237.2977 4746.916) (9239.8015 4743.6183) (9243.0992 4741.1145)
      (9247.1298 4739.4962) (9251.7863 4738.7786) (9256.9466 4738.9924) (9262.5038 4740.1221) (9268.2901 4742.1374)
      (9274.1985 4745.0076) (9280.0611 4748.6412) (9285.7405 4752.9618) (9291.0992 4757.8626) (9296.0 4763.2214)
      (9300.3206 4768.9008) (9303.9542 4774.7634) (9306.8244 4780.6718) (9308.855 4786.4733) (9309.9847 4792.0153)
      (9310.1832 4797.1756) (9309.4656 4801.8321) (9307.8473 4805.8626) (9305.3435 4809.1603) (9302.0458 4811.6641)
      (9298.0153 4813.2824) (9293.374 4814.0) (9288.1985 4813.8015) (9282.6565 4812.6718) (9276.855 4810.6412)
      (9270.9466 4807.771) (9265.084 4804.1374) (9259.4046 4799.8168) (9254.0458 4794.916) (9249.145 4789.5573)
      (9244.8244 4783.8779) (9241.1908 4778.0153) (9238.3206 4772.1069) (9236.3053 4766.3206) (9235.1756 4760.7634)
    ))
    ; P3150 -- see feature_dimensions_mm.csv
    ("06_ORNAMENT" 1 (
      (9234.9618 4648.9771) (9235.1756 4643.8168) (9236.3053 4638.2595) (9238.3206 4632.4733) (9241.1908 4626.5649)
      (9244.8244 4620.7023) (9249.145 4615.0229) (9254.0458 4609.6641) (9259.4046 4604.7634) (9265.084 4600.4427)
      (9270.9466 4596.8092) (9276.855 4593.9389) (9282.6565 4591.9084) (9288.1985 4590.7786) (9293.374 4590.5802)
      (9298.0153 4591.2977) (9302.0458 4592.916) (9305.3435 4595.4198) (9307.8473 4598.7176) (9309.4656 4602.7481)
      (9310.1832 4607.3893) (9309.9847 4612.5649) (9308.855 4618.1069) (9306.8244 4623.9084) (9303.9542 4629.8168)
      (9300.3206 4635.6794) (9296.0 4641.3588) (9291.0992 4646.7176) (9285.7405 4651.6183) (9280.0611 4655.9389)
      (9274.1985 4659.5725) (9268.2901 4662.4427) (9262.5038 4664.458) (9256.9466 4665.5878) (9251.7863 4665.8015)
      (9247.1298 4665.084) (9243.0992 4663.4656) (9239.8015 4660.9618) (9237.2977 4657.6641) (9235.6794 4653.6336)
    ))
    ; P3151 -- see feature_dimensions_mm.csv
    ("06_ORNAMENT" 1 (
      (9234.9618 4160.1832) (9235.6794 4155.5267) (9237.2977 4151.4962) (9239.8015 4148.1985) (9243.0992 4145.6947)
      (9247.1298 4144.0763) (9251.7863 4143.3588) (9256.9466 4143.5725) (9262.5038 4144.7023) (9268.2901 4146.7176)
      (9274.1985 4149.5878) (9280.0611 4153.2214) (9285.7405 4157.542) (9291.0992 4162.4427) (9296.0 4167.8015)
      (9300.3206 4173.4809) (9303.9542 4179.3435) (9306.8244 4185.2519) (9308.855 4191.0534) (9309.9847 4196.5954)
      (9310.1832 4201.7557) (9309.4656 4206.4122) (9307.8473 4210.4427) (9305.3435 4213.7405) (9302.0458 4216.2443)
      (9298.0153 4217.8626) (9293.374 4218.5802) (9288.1985 4218.3817) (9282.6565 4217.2519) (9276.855 4215.2214)
      (9270.9466 4212.3511) (9265.084 4208.7176) (9259.4046 4204.3969) (9254.0458 4199.4962) (9249.145 4194.1374)
      (9244.8244 4188.458) (9241.1908 4182.5954) (9238.3206 4176.687) (9236.3053 4170.9008) (9235.1756 4165.3435)
    ))
    ; P3152 -- see feature_dimensions_mm.csv
    ("06_ORNAMENT" 1 (
      (9234.9618 4053.5573) (9235.1756 4048.3969) (9236.3053 4042.8397) (9238.3206 4037.0534) (9241.1908 4031.145)
      (9244.8244 4025.2824) (9249.145 4019.6031) (9254.0458 4014.2443) (9259.4046 4009.3435) (9265.084 4005.0229)
      (9270.9466 4001.3893) (9276.855 3998.5191) (9282.6565 3996.4885) (9288.1985 3995.3588) (9293.374 3995.1603)
      (9298.0153 3995.8779) (9302.0458 3997.4962) (9305.3435 4000.0) (9307.8473 4003.2977) (9309.4656 4007.3282)
      (9310.1832 4011.9695) (9309.9847 4017.145) (9308.855 4022.687) (9306.8244 4028.4885) (9303.9542 4034.3969)
      (9300.3206 4040.2595) (9296.0 4045.9389) (9291.0992 4051.2977) (9285.7405 4056.1985) (9280.0611 4060.5191)
      (9274.1985 4064.1527) (9268.2901 4067.0229) (9262.5038 4069.0382) (9256.9466 4070.1679) (9251.7863 4070.3817)
      (9247.1298 4069.6641) (9243.0992 4068.0458) (9239.8015 4065.542) (9237.2977 4062.2443) (9235.6794 4058.2137)
    ))
    ; P3153 -- see feature_dimensions_mm.csv
    ("06_ORNAMENT" 1 (
      (9243.0992 5141.313) (9244.0916 5135.084) (9246.9466 5129.4656) (9251.4046 5125.0076) (9257.0229 5122.1527)
      (9263.2519 5121.1603) (9269.4809 5122.1527) (9275.0992 5125.0076) (9279.5573 5129.4656) (9282.4275 5135.084)
      (9283.4046 5141.313) (9282.4275 5147.542) (9279.5573 5153.1603) (9275.0992 5157.6183) (9269.4809 5160.4733)
      (9263.2519 5161.4656) (9257.0229 5160.4733) (9251.4046 5157.6183) (9246.9466 5153.1603) (9244.0916 5147.542)
    ))
    ; P3154 -- see feature_dimensions_mm.csv
    ("06_ORNAMENT" 1 (
      (9243.0992 4858.687) (9244.0916 4852.458) (9246.9466 4846.8397) (9251.4046 4842.3817) (9257.0229 4839.5267)
      (9263.2519 4838.5344) (9269.4809 4839.5267) (9275.0992 4842.3817) (9279.5573 4846.8397) (9282.4275 4852.458)
      (9283.4046 4858.687) (9282.4275 4864.916) (9279.5573 4870.5344) (9275.0992 4874.9924) (9269.4809 4877.8473)
      (9263.2519 4878.8397) (9257.0229 4877.8473) (9251.4046 4874.9924) (9246.9466 4870.5344) (9244.0916 4864.916)
    ))
    ; P3155 -- see feature_dimensions_mm.csv
    ("06_ORNAMENT" 1 (
      (9243.0992 4545.8931) (9244.0916 4539.6641) (9246.9466 4534.0458) (9251.4046 4529.5878) (9257.0229 4526.7328)
      (9263.2519 4525.7405) (9269.4809 4526.7328) (9275.0992 4529.5878) (9279.5573 4534.0458) (9282.4275 4539.6641)
      (9283.4046 4545.8931) (9282.4275 4552.1221) (9279.5573 4557.7405) (9275.0992 4562.1985) (9269.4809 4565.0534)
      (9263.2519 4566.0458) (9257.0229 4565.0534) (9251.4046 4562.1985) (9246.9466 4557.7405) (9244.0916 4552.1221)
    ))
    ; P3156 -- see feature_dimensions_mm.csv
    ("06_ORNAMENT" 1 (
      (9243.0992 4263.2672) (9244.0916 4257.0382) (9246.9466 4251.4198) (9251.4046 4246.9618) (9257.0229 4244.1069)
      (9263.2519 4243.1145) (9269.4809 4244.1069) (9275.0992 4246.9618) (9279.5573 4251.4198) (9282.4275 4257.0382)
      (9283.4046 4263.2672) (9282.4275 4269.4962) (9279.5573 4275.1145) (9275.0992 4279.5725) (9269.4809 4282.4275)
      (9263.2519 4283.4198) (9257.0229 4282.4275) (9251.4046 4279.5725) (9246.9466 4275.1145) (9244.0916 4269.4962)
    ))
    ; P3157 -- see feature_dimensions_mm.csv
    ("06_ORNAMENT" 1 (
      (9243.0992 3950.4733) (9244.0916 3944.2443) (9246.9466 3938.626) (9251.4046 3934.1679) (9257.0229 3931.313)
      (9263.2519 3930.3206) (9269.4809 3931.313) (9275.0992 3934.1679) (9279.5573 3938.626) (9282.4275 3944.2443)
      (9283.4046 3950.4733) (9282.4275 3956.7023) (9279.5573 3962.3206) (9275.0992 3966.7786) (9269.4809 3969.6336)
      (9263.2519 3970.626) (9257.0229 3969.6336) (9251.4046 3966.7786) (9246.9466 3962.3206) (9244.0916 3956.7023)
    ))
    ; P3158 -- see feature_dimensions_mm.csv
    ("06_ORNAMENT" 1 (
      (9256.916 5297.7099) (9257.4809 5293.6183) (9259.1908 5289.6183) (9261.9695 5285.8168) (9265.771 5282.3053)
      (9270.4885 5279.1908) (9276.0153 5276.5191) (9282.229 5274.3664) (9288.9466 5272.7939) (9296.0153 5271.8321)
      (9303.2672 5271.5115) (9310.5191 5271.8321) (9317.5878 5272.7939) (9324.3053 5274.3664) (9330.5191 5276.5191)
      (9336.0458 5279.1908) (9340.7634 5282.3053) (9344.5649 5285.8168) (9347.3435 5289.6183) (9349.0534 5293.6183)
      (9349.6183 5297.7099) (9349.0534 5301.8015) (9347.3435 5305.8015) (9344.5649 5309.6031) (9340.7634 5313.1145)
      (9336.0458 5316.229) (9330.5191 5318.9008) (9324.3053 5321.0534) (9317.5878 5322.626) (9310.5191 5323.5878)
      (9303.2672 5323.9084) (9296.0153 5323.5878) (9288.9466 5322.626) (9282.229 5321.0534) (9276.0153 5318.9008)
      (9270.4885 5316.229) (9265.771 5313.1145) (9261.9695 5309.6031) (9259.1908 5305.8015) (9257.4809 5301.8015)
    ))
    ; P3159 -- see feature_dimensions_mm.csv
    ("06_ORNAMENT" 1 (
      (9256.916 4702.2901) (9257.4809 4698.1985) (9259.1908 4694.1985) (9261.9695 4690.3969) (9265.771 4686.8855)
      (9270.4885 4683.771) (9276.0153 4681.0992) (9282.229 4678.9466) (9288.9466 4677.374) (9296.0153 4676.4122)
      (9303.2672 4676.0916) (9310.5191 4676.4122) (9317.5878 4677.374) (9324.3053 4678.9466) (9330.5191 4681.0992)
      (9336.0458 4683.771) (9340.7634 4686.8855) (9344.5649 4690.3969) (9347.3435 4694.1985) (9349.0534 4698.1985)
      (9349.6183 4702.2901) (9349.0534 4706.3817) (9347.3435 4710.3817) (9344.5649 4714.1832) (9340.7634 4717.6947)
      (9336.0458 4720.8092) (9330.5191 4723.4809) (9324.3053 4725.6336) (9317.5878 4727.2061) (9310.5191 4728.1679)
      (9303.2672 4728.4885) (9296.0153 4728.1679) (9288.9466 4727.2061) (9282.229 4725.6336) (9276.0153 4723.4809)
      (9270.4885 4720.8092) (9265.771 4717.6947) (9261.9695 4714.1832) (9259.1908 4710.3817) (9257.4809 4706.3817)
    ))
    ; P3160 -- see feature_dimensions_mm.csv
    ("06_ORNAMENT" 1 (
      (9256.916 4106.8702) (9257.4809 4102.7786) (9259.1908 4098.7786) (9261.9695 4094.9771) (9265.771 4091.4656)
      (9270.4885 4088.3511) (9276.0153 4085.6794) (9282.229 4083.5267) (9288.9466 4081.9542) (9296.0153 4080.9924)
      (9303.2672 4080.6718) (9310.5191 4080.9924) (9317.5878 4081.9542) (9324.3053 4083.5267) (9330.5191 4085.6794)
      (9336.0458 4088.3511) (9340.7634 4091.4656) (9344.5649 4094.9771) (9347.3435 4098.7786) (9349.0534 4102.7786)
      (9349.6183 4106.8702) (9349.0534 4110.9618) (9347.3435 4114.9618) (9344.5649 4118.7634) (9340.7634 4122.2748)
      (9336.0458 4125.3893) (9330.5191 4128.0611) (9324.3053 4130.2137) (9317.5878 4131.7863) (9310.5191 4132.7481)
      (9303.2672 4133.0687) (9296.0153 4132.7481) (9288.9466 4131.7863) (9282.229 4130.2137) (9276.0153 4128.0611)
      (9270.4885 4125.3893) (9265.771 4122.2748) (9261.9695 4118.7634) (9259.1908 4114.9618) (9257.4809 4110.9618)
    ))
    ; P3161 -- see feature_dimensions_mm.csv
    ("06_ORNAMENT" 1 (
      (9270.3817 5102.2137) (9271.6031 5097.6794) (9274.916 5094.3664) (9279.4504 5093.145) (9283.9847 5094.3664)
      (9287.2977 5097.6794) (9288.5191 5102.2137) (9287.2977 5106.7481) (9283.9847 5110.0611) (9279.4504 5111.2824)
      (9274.916 5110.0611) (9271.6031 5106.7481)
    ))
    ; P3162 -- see feature_dimensions_mm.csv
    ("06_ORNAMENT" 1 (
      (9270.3817 4897.7863) (9271.6031 4893.2519) (9274.916 4889.9389) (9279.4504 4888.7176) (9283.9847 4889.9389)
      (9287.2977 4893.2519) (9288.5191 4897.7863) (9287.2977 4902.3206) (9283.9847 4905.6336) (9279.4504 4906.855)
      (9274.916 4905.6336) (9271.6031 4902.3206)
    ))
    ; P3163 -- see feature_dimensions_mm.csv
    ("06_ORNAMENT" 1 (
      (9270.3817 4506.7939) (9271.6031 4502.2595) (9274.916 4498.9466) (9279.4504 4497.7252) (9283.9847 4498.9466)
      (9287.2977 4502.2595) (9288.5191 4506.7939) (9287.2977 4511.3282) (9283.9847 4514.6412) (9279.4504 4515.8626)
      (9274.916 4514.6412) (9271.6031 4511.3282)
    ))
    ; P3164 -- see feature_dimensions_mm.csv
    ("06_ORNAMENT" 1 (
      (9270.3817 4302.3664) (9271.6031 4297.8321) (9274.916 4294.5191) (9279.4504 4293.2977) (9283.9847 4294.5191)
      (9287.2977 4297.8321) (9288.5191 4302.3664) (9287.2977 4306.9008) (9283.9847 4310.2137) (9279.4504 4311.4351)
      (9274.916 4310.2137) (9271.6031 4306.9008)
    ))
    ; P3165 -- see feature_dimensions_mm.csv
    ("06_ORNAMENT" 1 (
      (9270.3817 3911.374) (9271.6031 3906.8397) (9274.916 3903.5267) (9279.4504 3902.3053) (9283.9847 3903.5267)
      (9287.2977 3906.8397) (9288.5191 3911.374) (9287.2977 3915.9084) (9283.9847 3919.2214) (9279.4504 3920.4427)
      (9274.916 3919.2214) (9271.6031 3915.9084)
    ))
    ; P3166 -- see feature_dimensions_mm.csv
    ("06_ORNAMENT" 1 (
      (9296.1832 5007.6336) (9296.5954 5005.0534) (9297.7863 5002.626) (9299.6794 5000.4275) (9302.1374 4998.5954)
      (9304.9771 4997.145) (9308.0 4996.0916) (9311.0382 4995.374) (9313.8779 4994.9313) (9316.3969 4994.6107)
      (9318.4885 4994.2901) (9320.1221 4993.8168) (9321.2824 4993.0382) (9322.0611 4991.8779) (9322.5344 4990.2443)
      (9322.855 4988.1527) (9323.1756 4985.6336) (9323.6183 4982.7939) (9324.3359 4979.7557) (9325.3893 4976.7328)
      (9326.8397 4973.8931) (9328.6718 4971.4351) (9330.8702 4969.542) (9333.2977 4968.3511) (9335.8779 4967.9389)
      (9338.458 4968.3511) (9340.8855 4969.542) (9343.084 4971.4351) (9344.916 4973.8931) (9346.3664 4976.7328)
      (9347.4198 4979.7557) (9348.1374 4982.7939) (9348.5802 4985.6336) (9348.9008 4988.1527) (9349.2214 4990.2443)
      (9349.6947 4991.8779) (9350.4733 4993.0382) (9351.6336 4993.8168) (9353.2672 4994.2901) (9355.3588 4994.6107)
      (9357.8779 4994.9313) (9360.7176 4995.374) (9363.7557 4996.0916) (9366.7786 4997.145) (9369.6183 4998.5954)
      (9372.0763 5000.4275) (9373.9695 5002.626) (9375.1603 5005.0534) (9375.5725 5007.6336) (9375.1603 5010.2137)
      (9373.9695 5012.6412) (9372.0763 5014.8397) (9369.6183 5016.6718) (9366.7786 5018.1221) (9363.7557 5019.1756)
      (9360.7176 5019.8931) (9357.8779 5020.3359) (9355.3588 5020.6565) (9353.2672 5020.9771) (9351.6336 5021.4504)
      (9350.4733 5022.229) (9349.6947 5023.3893) (9349.2214 5025.0229) (9348.9008 5027.1145) (9348.5802 5029.6336)
      (9348.1374 5032.4733) (9347.4198 5035.5115) (9346.3664 5038.5344) (9344.916 5041.374) (9343.084 5043.8321)
      (9340.8855 5045.7252) (9338.458 5046.916) (9335.8779 5047.3282) (9333.2977 5046.916) (9330.8702 5045.7252)
      (9328.6718 5043.8321) (9326.8397 5041.374) (9325.3893 5038.5344) (9324.3359 5035.5115) (9323.6183 5032.4733)
      (9323.1756 5029.6336) (9322.855 5027.1145) (9322.5344 5025.0229) (9322.0611 5023.3893) (9321.2824 5022.229)
      (9320.1221 5021.4504) (9318.4885 5020.9771) (9316.3969 5020.6565) (9313.8779 5020.3359) (9311.0382 5019.8931)
      (9308.0 5019.1756) (9304.9771 5018.1221) (9302.1374 5016.6718) (9299.6794 5014.8397) (9297.7863 5012.6412)
      (9296.5954 5010.2137)
    ))
    ; P3167 -- see feature_dimensions_mm.csv
    ("06_ORNAMENT" 1 (
      (9334.7176 5362.4885) (9335.7099 5356.2595) (9338.5649 5350.6412) (9343.0229 5346.1832) (9348.6412 5343.3282)
      (9354.8702 5342.3359) (9361.0992 5343.3282) (9366.7176 5346.1832) (9371.1756 5350.6412) (9374.0305 5356.2595)
      (9375.0229 5362.4885) (9374.0305 5368.7176) (9371.1756 5374.3359) (9366.7176 5378.7939) (9361.0992 5381.6641)
      (9354.8702 5382.6412) (9348.6412 5381.6641) (9343.0229 5378.7939) (9338.5649 5374.3359) (9335.7099 5368.7176)
    ))
    ; P3168 -- see feature_dimensions_mm.csv
    ("06_ORNAMENT" 1 (
      (9334.7176 5232.9313) (9335.7099 5226.7023) (9338.5649 5221.084) (9343.0229 5216.626) (9348.6412 5213.7557)
      (9354.8702 5212.7786) (9361.0992 5213.7557) (9366.7176 5216.626) (9371.1756 5221.084) (9374.0305 5226.7023)
      (9375.0229 5232.9313) (9374.0305 5239.1603) (9371.1756 5244.7786) (9366.7176 5249.2366) (9361.0992 5252.0916)
      (9354.8702 5253.084) (9348.6412 5252.0916) (9343.0229 5249.2366) (9338.5649 5244.7786) (9335.7099 5239.1603)
    ))
    ; P3169 -- see feature_dimensions_mm.csv
    ("06_ORNAMENT" 1 (
      (9334.7176 4767.0687) (9335.7099 4760.8397) (9338.5649 4755.2214) (9343.0229 4750.7634) (9348.6412 4747.9084)
      (9354.8702 4746.916) (9361.0992 4747.9084) (9366.7176 4750.7634) (9371.1756 4755.2214) (9374.0305 4760.8397)
      (9375.0229 4767.0687) (9374.0305 4773.2977) (9371.1756 4778.916) (9366.7176 4783.374) (9361.0992 4786.2443)
      (9354.8702 4787.2214) (9348.6412 4786.2443) (9343.0229 4783.374) (9338.5649 4778.916) (9335.7099 4773.2977)
    ))
    ; P3170 -- see feature_dimensions_mm.csv
    ("06_ORNAMENT" 1 (
      (9334.7176 4637.5115) (9335.7099 4631.2824) (9338.5649 4625.6641) (9343.0229 4621.2061) (9348.6412 4618.3359)
      (9354.8702 4617.3588) (9361.0992 4618.3359) (9366.7176 4621.2061) (9371.1756 4625.6641) (9374.0305 4631.2824)
      (9375.0229 4637.5115) (9374.0305 4643.7405) (9371.1756 4649.3588) (9366.7176 4653.8168) (9361.0992 4656.6718)
      (9354.8702 4657.6641) (9348.6412 4656.6718) (9343.0229 4653.8168) (9338.5649 4649.3588) (9335.7099 4643.7405)
    ))
    ; P3171 -- see feature_dimensions_mm.csv
    ("06_ORNAMENT" 1 (
      (9334.7176 4171.6489) (9335.7099 4165.4198) (9338.5649 4159.8015) (9343.0229 4155.3435) (9348.6412 4152.4885)
      (9354.8702 4151.4962) (9361.0992 4152.4885) (9366.7176 4155.3435) (9371.1756 4159.8015) (9374.0305 4165.4198)
      (9375.0229 4171.6489) (9374.0305 4177.8779) (9371.1756 4183.4962) (9366.7176 4187.9542) (9361.0992 4190.8244)
      (9354.8702 4191.8015) (9348.6412 4190.8244) (9343.0229 4187.9542) (9338.5649 4183.4962) (9335.7099 4177.8779)
    ))
    ; P3172 -- see feature_dimensions_mm.csv
    ("06_ORNAMENT" 1 (
      (9334.7176 4042.0916) (9335.7099 4035.8626) (9338.5649 4030.2443) (9343.0229 4025.7863) (9348.6412 4022.916)
      (9354.8702 4021.9389) (9361.0992 4022.916) (9366.7176 4025.7863) (9371.1756 4030.2443) (9374.0305 4035.8626)
      (9375.0229 4042.0916) (9374.0305 4048.3206) (9371.1756 4053.9389) (9366.7176 4058.3969) (9361.0992 4061.2519)
      (9354.8702 4062.2443) (9348.6412 4061.2519) (9343.0229 4058.3969) (9338.5649 4053.9389) (9335.7099 4048.3206)
    ))
    ; P3173 -- see feature_dimensions_mm.csv
    ("06_ORNAMENT" 1 (
      (9339.0382 5447.3282) (9340.2443 5442.7939) (9343.5725 5439.4809) (9348.1069 5438.2595) (9352.6412 5439.4809)
      (9355.9542 5442.7939) (9357.1756 5447.3282) (9355.9542 5451.8626) (9352.6412 5455.1908) (9348.1069 5456.3969)
      (9343.5725 5455.1908) (9340.2443 5451.8626)
    ))
    ; P3174 -- see feature_dimensions_mm.csv
    ("06_ORNAMENT" 1 (
      (9339.0382 5148.0763) (9340.2443 5143.542) (9343.5725 5140.229) (9348.1069 5139.0076) (9352.6412 5140.229)
      (9355.9542 5143.542) (9357.1756 5148.0763) (9355.9542 5152.6107) (9352.6412 5155.9389) (9348.1069 5157.145)
      (9343.5725 5155.9389) (9340.2443 5152.6107)
    ))
    ; P3175 -- see feature_dimensions_mm.csv
    ("06_ORNAMENT" 1 (
      (9339.0382 4851.9084) (9340.2443 4847.374) (9343.5725 4844.0611) (9348.1069 4842.8397) (9352.6412 4844.0611)
      (9355.9542 4847.374) (9357.1756 4851.9084) (9355.9542 4856.4427) (9352.6412 4859.771) (9348.1069 4860.9771)
      (9343.5725 4859.771) (9340.2443 4856.4427)
    ))
    ; P3176 -- see feature_dimensions_mm.csv
    ("06_ORNAMENT" 1 (
      (9339.0382 4552.6565) (9340.2443 4548.1221) (9343.5725 4544.8092) (9348.1069 4543.5878) (9352.6412 4544.8092)
      (9355.9542 4548.1221) (9357.1756 4552.6565) (9355.9542 4557.1908) (9352.6412 4560.5191) (9348.1069 4561.7252)
      (9343.5725 4560.5191) (9340.2443 4557.1908)
    ))
    ; P3177 -- see feature_dimensions_mm.csv
    ("06_ORNAMENT" 1 (
      (9339.0382 4256.4885) (9340.2443 4251.9542) (9343.5725 4248.6412) (9348.1069 4247.4198) (9352.6412 4248.6412)
      (9355.9542 4251.9542) (9357.1756 4256.4885) (9355.9542 4261.0229) (9352.6412 4264.3511) (9348.1069 4265.5573)
      (9343.5725 4264.3511) (9340.2443 4261.0229)
    ))
    ; P3178 -- see feature_dimensions_mm.csv
    ("06_ORNAMENT" 1 (
      (9339.0382 3957.2366) (9340.2443 3952.7176) (9343.5725 3949.3893) (9348.1069 3948.1679) (9352.6412 3949.3893)
      (9355.9542 3952.7176) (9357.1756 3957.2366) (9355.9542 3961.771) (9352.6412 3965.0992) (9348.1069 3966.3053)
      (9343.5725 3965.0992) (9340.2443 3961.771)
    ))
    ; P3179 -- see feature_dimensions_mm.csv
    ("06_ORNAMENT" 1 (
      (9384.9008 4783.2672) (9386.1221 4778.7328) (9389.4351 4775.4198) (9393.9695 4774.1985) (9398.5038 4775.4198)
      (9401.8168 4778.7328) (9403.0382 4783.2672) (9401.8168 4787.8015) (9398.5038 4791.1145) (9393.9695 4792.3359)
      (9389.4351 4791.1145) (9386.1221 4787.8015)
    ))
    ; P3180 -- see feature_dimensions_mm.csv
    ("06_ORNAMENT" 1 (
      (9384.9008 4621.313) (9386.1221 4616.7786) (9389.4351 4613.4656) (9393.9695 4612.2443) (9398.5038 4613.4656)
      (9401.8168 4616.7786) (9403.0382 4621.313) (9401.8168 4625.8473) (9398.5038 4629.1603) (9393.9695 4630.3817)
      (9389.4351 4629.1603) (9386.1221 4625.8473)
    ))
    ; P3181 -- see feature_dimensions_mm.csv
    ("06_ORNAMENT" 1 (
      (9384.9008 4187.8473) (9386.1221 4183.313) (9389.4351 4180.0) (9393.9695 4178.7786) (9398.5038 4180.0)
      (9401.8168 4183.313) (9403.0382 4187.8473) (9401.8168 4192.3817) (9398.5038 4195.6947) (9393.9695 4196.916)
      (9389.4351 4195.6947) (9386.1221 4192.3817)
    ))
    ; P3182 -- see feature_dimensions_mm.csv
    ("06_ORNAMENT" 1 (
      (9384.9008 4025.8931) (9386.1221 4021.3588) (9389.4351 4018.0458) (9393.9695 4016.8244) (9398.5038 4018.0458)
      (9401.8168 4021.3588) (9403.0382 4025.8931) (9401.8168 4030.4275) (9398.5038 4033.7405) (9393.9695 4034.9618)
      (9389.4351 4033.7405) (9386.1221 4030.4275)
    ))
    ; P3183 -- see feature_dimensions_mm.csv
    ("06_ORNAMENT" 1 (
      (9397.7099 5443.5573) (9398.9313 5437.4351) (9402.4122 5432.229) (9407.6031 5428.7481) (9413.7405 5427.5267)
      (9419.8779 5428.7481) (9425.0687 5432.229) (9428.5496 5437.4351) (9429.771 5443.5573) (9428.5496 5449.6947)
      (9425.0687 5454.9008) (9419.8779 5458.3664) (9413.7405 5459.5878) (9407.6031 5458.3664) (9402.4122 5454.9008)
      (9398.9313 5449.6947)
    ))
    ; P3184 -- see feature_dimensions_mm.csv
    ("06_ORNAMENT" 1 (
      (9397.7099 5138.2137) (9398.9313 5132.0916) (9402.4122 5126.8855) (9407.6031 5123.4046) (9413.7405 5122.1832)
      (9419.8779 5123.4046) (9425.0687 5126.8855) (9428.5496 5132.0916) (9429.771 5138.2137) (9428.5496 5144.3511)
      (9425.0687 5149.5573) (9419.8779 5153.0229) (9413.7405 5154.2443) (9407.6031 5153.0229) (9402.4122 5149.5573)
      (9398.9313 5144.3511)
    ))
    ; P3185 -- see feature_dimensions_mm.csv
    ("06_ORNAMENT" 1 (
      (9397.7099 5061.8779) (9398.9313 5055.7557) (9402.4122 5050.5496) (9407.6031 5047.0687) (9413.7405 5045.8473)
      (9419.8779 5047.0687) (9425.0687 5050.5496) (9428.5496 5055.7557) (9429.771 5061.8779) (9428.5496 5068.0153)
      (9425.0687 5073.2214) (9419.8779 5076.687) (9413.7405 5077.9084) (9407.6031 5076.687) (9402.4122 5073.2214)
      (9398.9313 5068.0153)
    ))
    ; P3186 -- see feature_dimensions_mm.csv
    ("06_ORNAMENT" 1 (
      (9397.7099 4985.542) (9398.9313 4979.4198) (9402.4122 4974.2137) (9407.6031 4970.7328) (9413.7405 4969.5115)
      (9419.8779 4970.7328) (9425.0687 4974.2137) (9428.5496 4979.4198) (9429.771 4985.542) (9428.5496 4991.6794)
      (9425.0687 4996.8855) (9419.8779 5000.3511) (9413.7405 5001.5725) (9407.6031 5000.3511) (9402.4122 4996.8855)
      (9398.9313 4991.6794)
    ))
    ; P3187 -- see feature_dimensions_mm.csv
    ("06_ORNAMENT" 1 (
      (9397.7099 4909.2061) (9398.9313 4903.084) (9402.4122 4897.8779) (9407.6031 4894.3969) (9413.7405 4893.1756)
      (9419.8779 4894.3969) (9425.0687 4897.8779) (9428.5496 4903.084) (9429.771 4909.2061) (9428.5496 4915.3435)
      (9425.0687 4920.5496) (9419.8779 4924.0153) (9413.7405 4925.2366) (9407.6031 4924.0153) (9402.4122 4920.5496)
      (9398.9313 4915.3435)
    ))
    ; P3188 -- see feature_dimensions_mm.csv
    ("06_ORNAMENT" 1 (
      (9397.7099 4832.8702) (9398.9313 4826.7481) (9402.4122 4821.542) (9407.6031 4818.0611) (9413.7405 4816.8397)
      (9419.8779 4818.0611) (9425.0687 4821.542) (9428.5496 4826.7481) (9429.771 4832.8702) (9428.5496 4839.0076)
      (9425.0687 4844.2137) (9419.8779 4847.6794) (9413.7405 4848.9008) (9407.6031 4847.6794) (9402.4122 4844.2137)
      (9398.9313 4839.0076)
    ))
    ; P3189 -- see feature_dimensions_mm.csv
    ("06_ORNAMENT" 1 (
      (9397.7099 4527.5267) (9398.9313 4521.4046) (9402.4122 4516.1985) (9407.6031 4512.7176) (9413.7405 4511.4962)
      (9419.8779 4512.7176) (9425.0687 4516.1985) (9428.5496 4521.4046) (9429.771 4527.5267) (9428.5496 4533.6641)
      (9425.0687 4538.8702) (9419.8779 4542.3359) (9413.7405 4543.5573) (9407.6031 4542.3359) (9402.4122 4538.8702)
      (9398.9313 4533.6641)
    ))
    ; P3190 -- see feature_dimensions_mm.csv
    ("06_ORNAMENT" 1 (
      (9397.7099 4374.855) (9398.9313 4368.7328) (9402.4122 4363.5267) (9407.6031 4360.0458) (9413.7405 4358.8244)
      (9419.8779 4360.0458) (9425.0687 4363.5267) (9428.5496 4368.7328) (9429.771 4374.855) (9428.5496 4380.9924)
      (9425.0687 4386.1985) (9419.8779 4389.6641) (9413.7405 4390.8855) (9407.6031 4389.6641) (9402.4122 4386.1985)
      (9398.9313 4380.9924)
    ))
    ; P3191 -- see feature_dimensions_mm.csv
    ("06_ORNAMENT" 1 (
      (9397.7099 4298.5191) (9398.9313 4292.3969) (9402.4122 4287.1908) (9407.6031 4283.7099) (9413.7405 4282.4885)
      (9419.8779 4283.7099) (9425.0687 4287.1908) (9428.5496 4292.3969) (9429.771 4298.5191) (9428.5496 4304.6565)
      (9425.0687 4309.8626) (9419.8779 4313.3282) (9413.7405 4314.5496) (9407.6031 4313.3282) (9402.4122 4309.8626)
      (9398.9313 4304.6565)
    ))
    ; P3192 -- see feature_dimensions_mm.csv
    ("06_ORNAMENT" 1 (
      (9397.7099 4222.1832) (9398.9313 4216.0611) (9402.4122 4210.855) (9407.6031 4207.374) (9413.7405 4206.1527)
      (9419.8779 4207.374) (9425.0687 4210.855) (9428.5496 4216.0611) (9429.771 4222.1832) (9428.5496 4228.3206)
      (9425.0687 4233.5267) (9419.8779 4236.9924) (9413.7405 4238.2137) (9407.6031 4236.9924) (9402.4122 4233.5267)
      (9398.9313 4228.3206)
    ))
    ; P3193 -- see feature_dimensions_mm.csv
    ("06_ORNAMENT" 1 (
      (9397.7099 3916.8397) (9398.9313 3910.7176) (9402.4122 3905.5115) (9407.6031 3902.0305) (9413.7405 3900.8092)
      (9419.8779 3902.0305) (9425.0687 3905.5115) (9428.5496 3910.7176) (9429.771 3916.8397) (9428.5496 3922.9771)
      (9425.0687 3928.1832) (9419.8779 3931.6489) (9413.7405 3932.8702) (9407.6031 3931.6489) (9402.4122 3928.1832)
      (9398.9313 3922.9771)
    ))
    ; P3194 -- see feature_dimensions_mm.csv
    ("06_ORNAMENT" 1 (
      (9401.0076 4106.8702) (9402.229 4102.3359) (9405.542 4099.0229) (9410.0763 4097.8015) (9414.6107 4099.0229)
      (9417.9237 4102.3359) (9419.145 4106.8702) (9417.9237 4111.4046) (9414.6107 4114.7176) (9410.0763 4115.9389)
      (9405.542 4114.7176) (9402.229 4111.4046)
    ))
    ; P3195 -- see feature_dimensions_mm.csv
    ("06_ORNAMENT" 1 (
      (9456.4885 7389.313) (9457.8473 7386.7939) (9461.5573 7384.7481) (9466.5954 7383.4198) (9471.6489 7382.7328)
      (9475.4351 7382.2748) (9477.1145 7381.4198) (9476.5191 7379.6183) (9474.1832 7376.6107) (9471.0992 7372.5496)
      (9468.4733 7368.0458) (9467.2977 7363.9847) (9468.1221 7361.2519) (9470.855 7360.4275) (9474.916 7361.6031)
      (9479.4198 7364.229) (9483.4809 7367.313) (9486.4885 7369.6489) (9488.2901 7370.2443) (9489.145 7368.5649)
      (9489.6031 7364.7786) (9490.3053 7359.7252) (9491.6183 7354.687) (9493.6641 7350.9771) (9496.1832 7349.6183)
      (9498.7023 7350.9771) (9500.7481 7354.687) (9502.0763 7359.7252) (9502.7634 7364.7786) (9503.2214 7368.5649)
      (9504.0763 7370.2443) (9505.8779 7369.6489) (9508.8855 7367.313) (9512.9466 7364.229) (9517.4504 7361.6031)
      (9521.5115 7360.4275) (9524.2443 7361.2519) (9525.0687 7363.9847) (9523.8931 7368.0458) (9521.2672 7372.5496)
      (9518.1832 7376.6107) (9515.8473 7379.6183) (9515.2519 7381.4198) (9516.9313 7382.2748) (9520.7176 7382.7328)
      (9525.771 7383.4198) (9530.8092 7384.7481) (9534.5191 7386.7939) (9535.8779 7389.313) (9534.5191 7391.8321)
      (9530.8092 7393.8779) (9525.771 7395.1908) (9520.7176 7395.8931) (9516.9313 7396.3511) (9515.2519 7397.2061)
      (9515.8473 7399.0076) (9518.1832 7402.0153) (9521.2672 7406.0763) (9523.8931 7410.5802) (9525.0687 7414.6412)
      (9524.2443 7417.374) (9521.5115 7418.1985) (9517.4504 7417.0229) (9512.9466 7414.3969) (9508.8855 7411.313)
      (9505.8779 7408.9771) (9504.0763 7408.3817) (9503.2214 7410.0611) (9502.7634 7413.8473) (9502.0763 7418.9008)
      (9500.7481 7423.9389) (9498.7023 7427.6489) (9496.1832 7429.0076) (9493.6641 7427.6489) (9491.6183 7423.9389)
      (9490.3053 7418.9008) (9489.6031 7413.8473) (9489.145 7410.0611) (9488.2901 7408.3817) (9486.4885 7408.9771)
      (9483.4809 7411.313) (9479.4198 7414.3969) (9474.916 7417.0229) (9470.855 7418.1985) (9468.1221 7417.374)
      (9467.2977 7414.6412) (9468.4733 7410.5802) (9471.0992 7406.0763) (9474.1832 7402.0153) (9476.5191 7399.0076)
      (9477.1145 7397.2061) (9475.4351 7396.3511) (9471.6489 7395.8931) (9466.5954 7395.1908) (9461.5573 7393.8779)
      (9457.8473 7391.8321)
    ))
    ; P3196 -- see feature_dimensions_mm.csv
    ("06_ORNAMENT" 1 (
      (9456.4885 7206.1069) (9457.8473 7203.5878) (9461.5573 7201.542) (9466.5954 7200.2137) (9471.6489 7199.5267)
      (9475.4351 7199.0687) (9477.1145 7198.2137) (9476.5191 7196.4122) (9474.1832 7193.4046) (9471.0992 7189.3435)
      (9468.4733 7184.8397) (9467.2977 7180.7786) (9468.1221 7178.0458) (9470.855 7177.2214) (9474.916 7178.3969)
      (9479.4198 7181.0229) (9483.4809 7184.1069) (9486.4885 7186.4427) (9488.2901 7187.0382) (9489.145 7185.3588)
      (9489.6031 7181.5725) (9490.3053 7176.5191) (9491.6183 7171.4809) (9493.6641 7167.771) (9496.1832 7166.4122)
      (9498.7023 7167.771) (9500.7481 7171.4809) (9502.0763 7176.5191) (9502.7634 7181.5725) (9503.2214 7185.3588)
      (9504.0763 7187.0382) (9505.8779 7186.4427) (9508.8855 7184.1069) (9512.9466 7181.0229) (9517.4504 7178.3969)
      (9521.5115 7177.2214) (9524.2443 7178.0458) (9525.0687 7180.7786) (9523.8931 7184.8397) (9521.2672 7189.3435)
      (9518.1832 7193.4046) (9515.8473 7196.4122) (9515.2519 7198.2137) (9516.9313 7199.0687) (9520.7176 7199.5267)
      (9525.771 7200.2137) (9530.8092 7201.542) (9534.5191 7203.5878) (9535.8779 7206.1069) (9534.5191 7208.626)
      (9530.8092 7210.6718) (9525.771 7211.9847) (9520.7176 7212.687) (9516.9313 7213.145) (9515.2519 7214.0)
      (9515.8473 7215.8015) (9518.1832 7218.8092) (9521.2672 7222.8702) (9523.8931 7227.374) (9525.0687 7231.4351)
      (9524.2443 7234.1679) (9521.5115 7234.9924) (9517.4504 7233.8168) (9512.9466 7231.1908) (9508.8855 7228.1069)
      (9505.8779 7225.771) (9504.0763 7225.1756) (9503.2214 7226.855) (9502.7634 7230.6412) (9502.0763 7235.6947)
      (9500.7481 7240.7328) (9498.7023 7244.4427) (9496.1832 7245.8015) (9493.6641 7244.4427) (9491.6183 7240.7328)
      (9490.3053 7235.6947) (9489.6031 7230.6412) (9489.145 7226.855) (9488.2901 7225.1756) (9486.4885 7225.771)
      (9483.4809 7228.1069) (9479.4198 7231.1908) (9474.916 7233.8168) (9470.855 7234.9924) (9468.1221 7234.1679)
      (9467.2977 7231.4351) (9468.4733 7227.374) (9471.0992 7222.8702) (9474.1832 7218.8092) (9476.5191 7215.8015)
      (9477.1145 7214.0) (9475.4351 7213.145) (9471.6489 7212.687) (9466.5954 7211.9847) (9461.5573 7210.6718)
      (9457.8473 7208.626)
    ))
    ; P3197 -- see feature_dimensions_mm.csv
    ("06_ORNAMENT" 1 (
      (9487.0534 7389.313) (9487.7557 7385.8168) (9489.7252 7382.855) (9492.687 7380.8855) (9496.1832 7380.1832)
      (9499.6794 7380.8855) (9502.6412 7382.855) (9504.6107 7385.8168) (9505.313 7389.313) (9504.6107 7392.8092)
      (9502.6412 7395.771) (9499.6794 7397.7405) (9496.1832 7398.4427) (9492.687 7397.7405) (9489.7252 7395.771)
      (9487.7557 7392.8092)
    ))
    ; P3198 -- see feature_dimensions_mm.csv
    ("06_ORNAMENT" 1 (
      (9487.0534 7206.1069) (9487.7557 7202.6107) (9489.7252 7199.6489) (9492.687 7197.6794) (9496.1832 7196.9771)
      (9499.6794 7197.6794) (9502.6412 7199.6489) (9504.6107 7202.6107) (9505.313 7206.1069) (9504.6107 7209.6031)
      (9502.6412 7212.5649) (9499.6794 7214.5344) (9496.1832 7215.2366) (9492.687 7214.5344) (9489.7252 7212.5649)
      (9487.7557 7209.6031)
    ))
    ; P3199 -- see feature_dimensions_mm.csv
    ("06_ORNAMENT" 1 (
      (9547.3282 5443.5573) (9548.5496 5437.4351) (9552.0305 5432.229) (9557.2214 5428.7481) (9563.3588 5427.5267)
      (9569.4962 5428.7481) (9574.687 5432.229) (9578.1679 5437.4351) (9579.3893 5443.5573) (9578.1679 5449.6947)
      (9574.687 5454.9008) (9569.4962 5458.3664) (9563.3588 5459.5878) (9557.2214 5458.3664) (9552.0305 5454.9008)
      (9548.5496 5449.6947)
    ))
    ; P3200 -- see feature_dimensions_mm.csv
    ("06_ORNAMENT" 1 (
      (9547.3282 5138.2137) (9548.5496 5132.0916) (9552.0305 5126.8855) (9557.2214 5123.4046) (9563.3588 5122.1832)
      (9569.4962 5123.4046) (9574.687 5126.8855) (9578.1679 5132.0916) (9579.3893 5138.2137) (9578.1679 5144.3511)
      (9574.687 5149.5573) (9569.4962 5153.0229) (9563.3588 5154.2443) (9557.2214 5153.0229) (9552.0305 5149.5573)
      (9548.5496 5144.3511)
    ))
    ; P3201 -- see feature_dimensions_mm.csv
    ("06_ORNAMENT" 1 (
      (9547.3282 5061.8779) (9548.5496 5055.7557) (9552.0305 5050.5496) (9557.2214 5047.0687) (9563.3588 5045.8473)
      (9569.4962 5047.0687) (9574.687 5050.5496) (9578.1679 5055.7557) (9579.3893 5061.8779) (9578.1679 5068.0153)
      (9574.687 5073.2214) (9569.4962 5076.687) (9563.3588 5077.9084) (9557.2214 5076.687) (9552.0305 5073.2214)
      (9548.5496 5068.0153)
    ))
    ; P3202 -- see feature_dimensions_mm.csv
    ("06_ORNAMENT" 1 (
      (9547.3282 4985.542) (9548.5496 4979.4198) (9552.0305 4974.2137) (9557.2214 4970.7328) (9563.3588 4969.5115)
      (9569.4962 4970.7328) (9574.687 4974.2137) (9578.1679 4979.4198) (9579.3893 4985.542) (9578.1679 4991.6794)
      (9574.687 4996.8855) (9569.4962 5000.3511) (9563.3588 5001.5725) (9557.2214 5000.3511) (9552.0305 4996.8855)
      (9548.5496 4991.6794)
    ))
    ; P3203 -- see feature_dimensions_mm.csv
    ("06_ORNAMENT" 1 (
      (9547.3282 4909.2061) (9548.5496 4903.084) (9552.0305 4897.8779) (9557.2214 4894.3969) (9563.3588 4893.1756)
      (9569.4962 4894.3969) (9574.687 4897.8779) (9578.1679 4903.084) (9579.3893 4909.2061) (9578.1679 4915.3435)
      (9574.687 4920.5496) (9569.4962 4924.0153) (9563.3588 4925.2366) (9557.2214 4924.0153) (9552.0305 4920.5496)
      (9548.5496 4915.3435)
    ))
    ; P3204 -- see feature_dimensions_mm.csv
    ("06_ORNAMENT" 1 (
      (9547.3282 4832.8702) (9548.5496 4826.7481) (9552.0305 4821.542) (9557.2214 4818.0611) (9563.3588 4816.8397)
      (9569.4962 4818.0611) (9574.687 4821.542) (9578.1679 4826.7481) (9579.3893 4832.8702) (9578.1679 4839.0076)
      (9574.687 4844.2137) (9569.4962 4847.6794) (9563.3588 4848.9008) (9557.2214 4847.6794) (9552.0305 4844.2137)
      (9548.5496 4839.0076)
    ))
    ; P3205 -- see feature_dimensions_mm.csv
    ("06_ORNAMENT" 1 (
      (9547.3282 4756.5344) (9548.5496 4750.4122) (9552.0305 4745.2061) (9554.7023 4743.4046) (9554.3664 4741.8321)
      (9551.771 4722.1374) (9550.9008 4702.2901) (9551.4046 4690.626) (9548.5496 4686.3359) (9547.3282 4680.1985)
      (9548.5496 4674.0763) (9552.0305 4668.8702) (9553.6947 4667.7405) (9554.3664 4662.7481) (9558.6565 4643.3435)
      (9564.6412 4624.3969) (9566.7786 4619.2214) (9563.3588 4619.8931) (9557.2214 4618.6718) (9552.0305 4615.2061)
      (9548.5496 4610.0) (9547.3282 4603.8626) (9548.5496 4597.7405) (9552.0305 4592.5344) (9557.2214 4589.0534)
      (9563.3588 4587.8321) (9569.4962 4589.0534) (9574.687 4592.5344) (9577.2672 4596.3817) (9581.4046 4588.4275)
      (9592.0916 4571.6794) (9604.1832 4555.9084) (9617.6031 4541.2672) (9632.2443 4527.8473) (9648.0153 4515.7557)
      (9664.7634 4505.0687) (9682.3817 4495.9084) (9700.7328 4488.3053) (9719.6794 4482.3206) (9739.084 4478.0305)
      (9758.7786 4475.4351) (9778.626 4474.5649) (9798.4733 4475.4351) (9818.1679 4478.0305) (9837.5725 4482.3206)
      (9856.5191 4488.3053) (9874.8702 4495.9084) (9892.4885 4505.0687) (9909.2366 4515.7557) (9925.0076 4527.8473)
      (9939.6489 4541.2672) (9953.0687 4555.9084) (9965.1603 4571.6794) (9975.8473 4588.4275) (9979.9847 4596.3817)
      (9982.5649 4592.5344) (9987.7557 4589.0534) (9993.8931 4587.8321) (10000.0305 4589.0534) (10005.2214 4592.5344)
      (10008.7023 4597.7405) (10009.9237 4603.8626) (10008.7023 4610.0) (10005.2214 4615.2061) (10000.0305 4618.6718)
      (9993.8931 4619.8931) (9990.4733 4619.2214) (9992.6107 4624.3969) (9998.5954 4643.3435) (10002.8855 4662.7481)
      (10003.5573 4667.7405) (10005.2214 4668.8702) (10008.7023 4674.0763) (10009.9237 4680.1985) (10008.7023 4686.3359)
      (10005.8473 4690.626) (10006.3511 4702.2901) (10005.4809 4722.1374) (10002.8855 4741.8321) (10002.5496 4743.4046)
      (10005.2214 4745.2061) (10008.7023 4750.4122) (10009.9237 4756.5344) (10008.7023 4762.6718) (10005.2214 4767.8779)
      (10000.0305 4771.3435) (9995.084 4772.3359) (9992.6107 4780.1832) (9985.0076 4798.5344) (9975.8473 4816.1527)
      (9965.1603 4832.9008) (9953.0687 4848.6718) (9939.6489 4863.313) (9925.0076 4876.7328) (9909.2366 4888.8244)
      (9892.4885 4899.5115) (9874.8702 4908.6718) (9856.5191 4916.2748) (9837.5725 4922.2595) (9818.1679 4926.5496)
      (9798.4733 4929.145) (9778.626 4930.0153) (9758.7786 4929.145) (9739.084 4926.5496) (9719.6794 4922.2595)
      (9700.7328 4916.2748) (9682.3817 4908.6718) (9664.7634 4899.5115) (9648.0153 4888.8244) (9632.2443 4876.7328)
      (9617.6031 4863.313) (9604.1832 4848.6718) (9592.0916 4832.9008) (9581.4046 4816.1527) (9572.2443 4798.5344)
      (9564.6412 4780.1832) (9562.1679 4772.3359) (9557.2214 4771.3435) (9552.0305 4767.8779) (9548.5496 4762.6718)
    ))
    ; P3206 -- see feature_dimensions_mm.csv
    ("06_ORNAMENT" 1 (
      (9547.3282 4527.5267) (9548.5496 4521.4046) (9552.0305 4516.1985) (9557.2214 4512.7176) (9563.3588 4511.4962)
      (9569.4962 4512.7176) (9574.687 4516.1985) (9578.1679 4521.4046) (9579.3893 4527.5267) (9578.1679 4533.6641)
      (9574.687 4538.8702) (9569.4962 4542.3359) (9563.3588 4543.5573) (9557.2214 4542.3359) (9552.0305 4538.8702)
      (9548.5496 4533.6641)
    ))
    ; P3207 -- see feature_dimensions_mm.csv
    ("06_ORNAMENT" 1 (
      (9547.3282 4374.855) (9548.5496 4368.7328) (9552.0305 4363.5267) (9557.2214 4360.0458) (9563.3588 4358.8244)
      (9569.4962 4360.0458) (9574.687 4363.5267) (9578.1679 4368.7328) (9579.3893 4374.855) (9578.1679 4380.9924)
      (9574.687 4386.1985) (9569.4962 4389.6641) (9563.3588 4390.8855) (9557.2214 4389.6641) (9552.0305 4386.1985)
      (9548.5496 4380.9924)
    ))
    ; P3208 -- see feature_dimensions_mm.csv
    ("06_ORNAMENT" 1 (
      (9547.3282 4298.5191) (9548.5496 4292.3969) (9552.0305 4287.1908) (9557.2214 4283.7099) (9563.3588 4282.4885)
      (9569.4962 4283.7099) (9574.687 4287.1908) (9578.1679 4292.3969) (9579.3893 4298.5191) (9578.1679 4304.6565)
      (9574.687 4309.8626) (9569.4962 4313.3282) (9563.3588 4314.5496) (9557.2214 4313.3282) (9552.0305 4309.8626)
      (9548.5496 4304.6565)
    ))
    ; P3209 -- see feature_dimensions_mm.csv
    ("06_ORNAMENT" 1 (
      (9547.3282 4222.1832) (9548.5496 4216.0611) (9552.0305 4210.855) (9557.2214 4207.374) (9563.3588 4206.1527)
      (9569.4962 4207.374) (9574.687 4210.855) (9578.1679 4216.0611) (9579.3893 4222.1832) (9578.1679 4228.3206)
      (9574.687 4233.5267) (9569.4962 4236.9924) (9563.3588 4238.2137) (9557.2214 4236.9924) (9552.0305 4233.5267)
      (9548.5496 4228.3206)
    ))
    ; P3210 -- see feature_dimensions_mm.csv
    ("06_ORNAMENT" 1 (
      (9547.3282 3916.8397) (9548.5496 3910.7176) (9552.0305 3905.5115) (9557.2214 3902.0305) (9563.3588 3900.8092)
      (9569.4962 3902.0305) (9574.687 3905.5115) (9578.1679 3910.7176) (9579.3893 3916.8397) (9578.1679 3922.9771)
      (9574.687 3928.1832) (9569.4962 3931.6489) (9563.3588 3932.8702) (9557.2214 3931.6489) (9552.0305 3928.1832)
      (9548.5496 3922.9771)
    ))
    ; P3211 -- see feature_dimensions_mm.csv
    ("06_ORNAMENT" 1 (
      (9557.9542 4106.8702) (9559.1756 4102.3359) (9562.4885 4099.0229) (9567.0229 4097.8015) (9571.5573 4099.0229)
      (9574.8702 4102.3359) (9576.0916 4106.8702) (9574.8702 4111.4046) (9571.5573 4114.7176) (9567.0229 4115.9389)
      (9562.4885 4114.7176) (9559.1756 4111.4046)
    ))
    ; P3212 -- see feature_dimensions_mm.csv
    ("06_ORNAMENT" 1 (
      (9574.0611 4783.2672) (9575.2824 4778.7328) (9578.5954 4775.4198) (9583.1298 4774.1985) (9587.6641 4775.4198)
      (9590.9771 4778.7328) (9592.1985 4783.2672) (9590.9771 4787.8015) (9587.6641 4791.1145) (9583.1298 4792.3359)
      (9578.5954 4791.1145) (9575.2824 4787.8015)
    ))
    ; P3213 -- see feature_dimensions_mm.csv
    ("06_ORNAMENT" 1 (
      (9574.0611 4621.313) (9575.2824 4616.7786) (9578.5954 4613.4656) (9583.1298 4612.2443) (9587.6641 4613.4656)
      (9590.9771 4616.7786) (9592.1985 4621.313) (9590.9771 4625.8473) (9587.6641 4629.1603) (9583.1298 4630.3817)
      (9578.5954 4629.1603) (9575.2824 4625.8473)
    ))
    ; P3214 -- see feature_dimensions_mm.csv
    ("06_ORNAMENT" 1 (
      (9574.0611 4187.8473) (9575.2824 4183.313) (9578.5954 4180.0) (9583.1298 4178.7786) (9587.6641 4180.0)
      (9590.9771 4183.313) (9592.1985 4187.8473) (9590.9771 4192.3817) (9587.6641 4195.6947) (9583.1298 4196.916)
      (9578.5954 4195.6947) (9575.2824 4192.3817)
    ))
    ; P3215 -- see feature_dimensions_mm.csv
    ("06_ORNAMENT" 1 (
      (9574.0611 4025.8931) (9575.2824 4021.3588) (9578.5954 4018.0458) (9583.1298 4016.8244) (9587.6641 4018.0458)
      (9590.9771 4021.3588) (9592.1985 4025.8931) (9590.9771 4030.4275) (9587.6641 4033.7405) (9583.1298 4034.9618)
      (9578.5954 4033.7405) (9575.2824 4030.4275)
    ))
    ; P3216 -- see feature_dimensions_mm.csv
    ("06_ORNAMENT" 1 (
      (9579.1145 4702.2901) (9579.4198 4699.2977) (9580.3053 4696.3664) (9581.4809 4694.1069) (9581.8779 4685.084)
      (9584.1374 4668.0) (9587.8626 4651.1756) (9593.0382 4634.7481) (9599.6336 4618.8244) (9607.5878 4603.542)
      (9616.8397 4589.0076) (9627.3282 4575.3435) (9633.4351 4568.687) (9634.1985 4566.229) (9635.6489 4563.542)
      (9637.5573 4561.2214) (9639.8779 4559.313) (9642.5649 4557.8626) (9645.0229 4557.0992) (9651.6794 4550.9924)
      (9665.3435 4540.5038) (9679.8779 4531.2519) (9695.1603 4523.2977) (9711.084 4516.7023) (9727.5115 4511.5267)
      (9744.3359 4507.8015) (9761.4198 4505.542) (9770.4427 4505.145) (9772.7023 4503.9695) (9775.6336 4503.0687)
      (9778.626 4502.7786) (9781.6183 4503.0687) (9784.5496 4503.9695) (9786.8092 4505.145) (9795.8321 4505.542)
      (9812.916 4507.8015) (9829.7405 4511.5267) (9846.1679 4516.7023) (9862.0916 4523.2977) (9877.374 4531.2519)
      (9891.9084 4540.5038) (9905.5725 4550.9924) (9912.229 4557.0992) (9914.687 4557.8626) (9917.374 4559.313)
      (9919.6947 4561.2214) (9921.6031 4563.542) (9923.0534 4566.229) (9923.8168 4568.687) (9929.9237 4575.3435)
      (9940.4122 4589.0076) (9949.6641 4603.542) (9957.6183 4618.8244) (9964.2137 4634.7481) (9969.3893 4651.1756)
      (9973.1145 4668.0) (9975.374 4685.084) (9975.771 4694.1069) (9976.9466 4696.3664) (9977.8473 4699.2977)
      (9978.1374 4702.2901) (9977.8473 4705.2824) (9976.9466 4708.2137) (9975.771 4710.4733) (9975.374 4719.4962)
      (9973.1145 4736.5802) (9969.3893 4753.4046) (9964.2137 4769.8321) (9957.6183 4785.7557) (9949.6641 4801.0382)
      (9940.4122 4815.5725) (9929.9237 4829.2366) (9923.8168 4835.8931) (9923.0534 4838.3511) (9921.6031 4841.0382)
      (9919.6947 4843.3588) (9917.374 4845.2672) (9914.687 4846.7176) (9912.229 4847.4809) (9905.5725 4853.5878)
      (9891.9084 4864.0763) (9877.374 4873.3282) (9862.0916 4881.2824) (9846.1679 4887.8779) (9829.7405 4893.0534)
      (9812.916 4896.7786) (9795.8321 4899.0382) (9786.8092 4899.4351) (9784.5496 4900.6107) (9781.6183 4901.4962)
      (9778.626 4901.8015) (9775.6336 4901.4962) (9772.7023 4900.6107) (9770.4427 4899.4351) (9761.4198 4899.0382)
      (9744.3359 4896.7786) (9727.5115 4893.0534) (9711.084 4887.8779) (9695.1603 4881.2824) (9679.8779 4873.3282)
      (9665.3435 4864.0763) (9651.6794 4853.5878) (9645.0229 4847.4809) (9642.5649 4846.7176) (9639.8779 4845.2672)
      (9637.5573 4843.3588) (9635.6489 4841.0382) (9634.1985 4838.3511) (9633.4351 4835.8931) (9627.3282 4829.2366)
      (9616.8397 4815.5725) (9607.5878 4801.0382) (9599.6336 4785.7557) (9593.0382 4769.8321) (9587.8626 4753.4046)
      (9584.1374 4736.5802) (9581.8779 4719.4962) (9581.4809 4710.4733) (9580.3053 4708.2137) (9579.4198 4705.2824)
    ))
    ; P3217 -- see feature_dimensions_mm.csv
    ("06_ORNAMENT" 1 (
      (9579.1145 4106.8702) (9579.4198 4103.8779) (9580.3053 4100.9466) (9581.4809 4098.687) (9581.8779 4089.6641)
      (9584.1374 4072.5802) (9587.8626 4055.7557) (9593.0382 4039.3282) (9599.6336 4023.4046) (9607.5878 4008.1221)
      (9616.8397 3993.5878) (9627.3282 3979.9237) (9633.4351 3973.2672) (9634.1985 3970.8092) (9635.6489 3968.1221)
      (9637.5573 3965.8015) (9639.8779 3963.8931) (9642.5649 3962.4427) (9645.0229 3961.6794) (9651.6794 3955.5725)
      (9665.3435 3945.084) (9679.8779 3935.8321) (9695.1603 3927.8779) (9711.084 3921.2824) (9727.5115 3916.1069)
      (9744.3359 3912.3817) (9761.4198 3910.1221) (9770.4427 3909.7252) (9772.7023 3908.5496) (9775.6336 3907.6489)
      (9778.626 3907.3588) (9781.6183 3907.6489) (9784.5496 3908.5496) (9786.8092 3909.7252) (9795.8321 3910.1221)
      (9812.916 3912.3817) (9829.7405 3916.1069) (9846.1679 3921.2824) (9862.0916 3927.8779) (9877.374 3935.8321)
      (9891.9084 3945.084) (9905.5725 3955.5725) (9912.229 3961.6794) (9914.687 3962.4427) (9917.374 3963.8931)
      (9919.6947 3965.8015) (9921.6031 3968.1221) (9923.0534 3970.8092) (9923.8168 3973.2672) (9929.9237 3979.9237)
      (9940.4122 3993.5878) (9949.6641 4008.1221) (9957.6183 4023.4046) (9964.2137 4039.3282) (9969.3893 4055.7557)
      (9973.1145 4072.5802) (9975.374 4089.6641) (9975.771 4098.687) (9976.9466 4100.9466) (9977.8473 4103.8779)
      (9978.1374 4106.8702) (9977.8473 4109.8626) (9976.9466 4112.7939) (9975.771 4115.0534) (9975.374 4124.0763)
      (9973.1145 4141.1603) (9969.3893 4157.9847) (9964.2137 4174.4122) (9957.6183 4190.3359) (9949.6641 4205.6183)
      (9940.4122 4220.1527) (9929.9237 4233.8168) (9923.8168 4240.4733) (9923.0534 4242.9313) (9921.6031 4245.6183)
      (9919.6947 4247.9389) (9917.374 4249.8473) (9914.687 4251.2977) (9912.229 4252.0611) (9905.5725 4258.1679)
      (9891.9084 4268.6565) (9877.374 4277.9084) (9862.0916 4285.8626) (9846.1679 4292.458) (9829.7405 4297.6336)
      (9812.916 4301.3588) (9795.8321 4303.6183) (9786.8092 4304.0153) (9784.5496 4305.1908) (9781.6183 4306.0763)
      (9778.626 4306.3817) (9775.6336 4306.0763) (9772.7023 4305.1908) (9770.4427 4304.0153) (9761.4198 4303.6183)
      (9744.3359 4301.3588) (9727.5115 4297.6336) (9711.084 4292.458) (9695.1603 4285.8626) (9679.8779 4277.9084)
      (9665.3435 4268.6565) (9651.6794 4258.1679) (9645.0229 4252.0611) (9642.5649 4251.2977) (9639.8779 4249.8473)
      (9637.5573 4247.9389) (9635.6489 4245.6183) (9634.1985 4242.9313) (9633.4351 4240.4733) (9627.3282 4233.8168)
      (9616.8397 4220.1527) (9607.5878 4205.6183) (9599.6336 4190.3359) (9593.0382 4174.4122) (9587.8626 4157.9847)
      (9584.1374 4141.1603) (9581.8779 4124.0763) (9581.4809 4115.0534) (9580.3053 4112.7939) (9579.4198 4109.8626)
    ))
    ; P3218 -- see feature_dimensions_mm.csv
    ("06_ORNAMENT" 1 (
      (9601.5267 5007.6336) (9601.9389 5005.0534) (9603.1298 5002.626) (9605.0229 5000.4275) (9607.4809 4998.5954)
      (9610.3206 4997.145) (9613.3435 4996.0916) (9616.3817 4995.374) (9619.2214 4994.9313) (9621.7405 4994.6107)
      (9623.8321 4994.2901) (9625.4656 4993.8168) (9626.626 4993.0382) (9627.4046 4991.8779) (9627.8779 4990.2443)
      (9628.1985 4988.1527) (9628.5191 4985.6336) (9628.9618 4982.7939) (9629.6794 4979.7557) (9630.7328 4976.7328)
      (9632.1832 4973.8931) (9634.0153 4971.4351) (9636.2137 4969.542) (9638.6412 4968.3511) (9641.2214 4967.9389)
      (9643.8015 4968.3511) (9646.229 4969.542) (9648.4275 4971.4351) (9650.2595 4973.8931) (9651.7099 4976.7328)
      (9652.7634 4979.7557) (9653.4809 4982.7939) (9653.9237 4985.6336) (9654.2443 4988.1527) (9654.5649 4990.2443)
      (9655.0382 4991.8779) (9655.8168 4993.0382) (9656.9771 4993.8168) (9658.6107 4994.2901) (9660.7023 4994.6107)
      (9663.2214 4994.9313) (9666.0611 4995.374) (9669.0992 4996.0916) (9672.1221 4997.145) (9674.9618 4998.5954)
      (9677.4198 5000.4275) (9679.313 5002.626) (9680.5038 5005.0534) (9680.916 5007.6336) (9680.5038 5010.2137)
      (9679.313 5012.6412) (9677.4198 5014.8397) (9674.9618 5016.6718) (9672.1221 5018.1221) (9669.0992 5019.1756)
      (9666.0611 5019.8931) (9663.2214 5020.3359) (9660.7023 5020.6565) (9658.6107 5020.9771) (9656.9771 5021.4504)
      (9655.8168 5022.229) (9655.0382 5023.3893) (9654.5649 5025.0229) (9654.2443 5027.1145) (9653.9237 5029.6336)
      (9653.4809 5032.4733) (9652.7634 5035.5115) (9651.7099 5038.5344) (9650.2595 5041.374) (9648.4275 5043.8321)
      (9646.229 5045.7252) (9643.8015 5046.916) (9641.2214 5047.3282) (9638.6412 5046.916) (9636.2137 5045.7252)
      (9634.0153 5043.8321) (9632.1832 5041.374) (9630.7328 5038.5344) (9629.6794 5035.5115) (9628.9618 5032.4733)
      (9628.5191 5029.6336) (9628.1985 5027.1145) (9627.8779 5025.0229) (9627.4046 5023.3893) (9626.626 5022.229)
      (9625.4656 5021.4504) (9623.8321 5020.9771) (9621.7405 5020.6565) (9619.2214 5020.3359) (9616.3817 5019.8931)
      (9613.3435 5019.1756) (9610.3206 5018.1221) (9607.4809 5016.6718) (9605.0229 5014.8397) (9603.1298 5012.6412)
      (9601.9389 5010.2137)
    ))
    ; P3219 -- see feature_dimensions_mm.csv
    ("06_ORNAMENT" 1 (
      (9601.5267 4412.2137) (9601.9389 4409.6336) (9603.1298 4407.2061) (9605.0229 4405.0076) (9607.4809 4403.1756)
      (9610.3206 4401.7252) (9613.3435 4400.6718) (9616.3817 4399.9542) (9619.2214 4399.5115) (9621.7405 4399.1908)
      (9623.8321 4398.8702) (9625.4656 4398.3969) (9626.626 4397.6183) (9627.4046 4396.458) (9627.8779 4394.8244)
      (9628.1985 4392.7328) (9628.5191 4390.2137) (9628.9618 4387.374) (9629.6794 4384.3359) (9630.7328 4381.313)
      (9632.1832 4378.4733) (9634.0153 4376.0153) (9636.2137 4374.1221) (9638.6412 4372.9313) (9641.2214 4372.5191)
      (9643.8015 4372.9313) (9646.229 4374.1221) (9648.4275 4376.0153) (9650.2595 4378.4733) (9651.7099 4381.313)
      (9652.7634 4384.3359) (9653.4809 4387.374) (9653.9237 4390.2137) (9654.2443 4392.7328) (9654.5649 4394.8244)
      (9655.0382 4396.458) (9655.8168 4397.6183) (9656.9771 4398.3969) (9658.6107 4398.8702) (9660.7023 4399.1908)
      (9663.2214 4399.5115) (9666.0611 4399.9542) (9669.0992 4400.6718) (9672.1221 4401.7252) (9674.9618 4403.1756)
      (9677.4198 4405.0076) (9679.313 4407.2061) (9680.5038 4409.6336) (9680.916 4412.2137)
    ))
    ; P3220 -- see feature_dimensions_mm.csv
    ("06_ORNAMENT" 1 (
      (9602.0763 5362.4885) (9603.0687 5356.2595) (9605.9237 5350.6412) (9610.3817 5346.1832) (9616.0 5343.3282)
      (9622.229 5342.3359) (9628.458 5343.3282) (9634.0763 5346.1832) (9638.5344 5350.6412) (9641.3893 5356.2595)
      (9642.3817 5362.4885) (9641.3893 5368.7176) (9638.5344 5374.3359) (9634.0763 5378.7939) (9628.458 5381.6641)
      (9622.229 5382.6412) (9616.0 5381.6641) (9610.3817 5378.7939) (9605.9237 5374.3359) (9603.0687 5368.7176)
    ))
    ; P3221 -- see feature_dimensions_mm.csv
    ("06_ORNAMENT" 1 (
      (9602.0763 5232.9313) (9603.0687 5226.7023) (9605.9237 5221.084) (9610.3817 5216.626) (9616.0 5213.7557)
      (9622.229 5212.7786) (9628.458 5213.7557) (9634.0763 5216.626) (9638.5344 5221.084) (9641.3893 5226.7023)
      (9642.3817 5232.9313) (9641.3893 5239.1603) (9638.5344 5244.7786) (9634.0763 5249.2366) (9628.458 5252.0916)
      (9622.229 5253.084) (9616.0 5252.0916) (9610.3817 5249.2366) (9605.9237 5244.7786) (9603.0687 5239.1603)
    ))
    ; P3222 -- see feature_dimensions_mm.csv
    ("06_ORNAMENT" 1 (
      (9602.0763 4767.0687) (9603.0687 4760.8397) (9605.9237 4755.2214) (9610.3817 4750.7634) (9616.0 4747.9084)
      (9622.229 4746.916) (9628.458 4747.9084) (9634.0763 4750.7634) (9638.5344 4755.2214) (9641.3893 4760.8397)
      (9642.3817 4767.0687) (9641.3893 4773.2977) (9638.5344 4778.916) (9634.0763 4783.374) (9628.458 4786.2443)
      (9622.229 4787.2214) (9616.0 4786.2443) (9610.3817 4783.374) (9605.9237 4778.916) (9603.0687 4773.2977)
    ))
    ; P3223 -- see feature_dimensions_mm.csv
    ("06_ORNAMENT" 1 (
      (9602.0763 4637.5115) (9603.0687 4631.2824) (9605.9237 4625.6641) (9610.3817 4621.2061) (9616.0 4618.3359)
      (9622.229 4617.3588) (9628.458 4618.3359) (9634.0763 4621.2061) (9638.5344 4625.6641) (9641.3893 4631.2824)
      (9642.3817 4637.5115) (9641.3893 4643.7405) (9638.5344 4649.3588) (9634.0763 4653.8168) (9628.458 4656.6718)
      (9622.229 4657.6641) (9616.0 4656.6718) (9610.3817 4653.8168) (9605.9237 4649.3588) (9603.0687 4643.7405)
    ))
    ; P3224 -- see feature_dimensions_mm.csv
    ("06_ORNAMENT" 1 (
      (9602.0763 4171.6489) (9603.0687 4165.4198) (9605.9237 4159.8015) (9610.3817 4155.3435) (9616.0 4152.4885)
      (9622.229 4151.4962) (9628.458 4152.4885) (9634.0763 4155.3435) (9638.5344 4159.8015) (9641.3893 4165.4198)
      (9642.3817 4171.6489) (9641.3893 4177.8779) (9638.5344 4183.4962) (9634.0763 4187.9542) (9628.458 4190.8244)
      (9622.229 4191.8015) (9616.0 4190.8244) (9610.3817 4187.9542) (9605.9237 4183.4962) (9603.0687 4177.8779)
    ))
    ; P3225 -- see feature_dimensions_mm.csv
    ("06_ORNAMENT" 1 (
      (9602.0763 4042.0916) (9603.0687 4035.8626) (9605.9237 4030.2443) (9610.3817 4025.7863) (9616.0 4022.916)
      (9622.229 4021.9389) (9628.458 4022.916) (9634.0763 4025.7863) (9638.5344 4030.2443) (9641.3893 4035.8626)
      (9642.3817 4042.0916) (9641.3893 4048.3206) (9638.5344 4053.9389) (9634.0763 4058.3969) (9628.458 4061.2519)
      (9622.229 4062.2443) (9616.0 4061.2519) (9610.3817 4058.3969) (9605.9237 4053.9389) (9603.0687 4048.3206)
    ))
    ; P3226 -- see feature_dimensions_mm.csv
    ("06_ORNAMENT" 1 (
      (9618.3206 3145.0382) (9648.4427 3141.9695) (9681.8015 3139.771) (9717.8473 3138.4427) (9756.0458 3138.0153)
      (9795.8626 3138.5496) (9836.7328 3140.0458) (9878.1374 3142.5649) (9919.542 3146.1069) (9960.3817 3150.7176)
      (10000.1221 3156.4275) (10015.084 3159.0992) (10003.3588 3155.0992) (9967.4046 3141.3893) (9931.374 3126.3359)
      (9895.7099 3110.229) (9860.8855 3093.3588) (9827.3435 3076.0305) (9795.5267 3058.5191) (9765.9084 3041.0992)
      (9738.916 3024.0763) (9715.0076 3007.7405) (9694.6565 2992.3664) (9722.2595 2998.4885) (9752.4275 3006.3969)
      (9784.6718 3015.9237) (9818.5038 3026.9618) (9853.4504 3039.374) (9889.0229 3053.0229) (9924.7176 3067.771)
      (9960.0611 3083.4962) (9994.5649 3100.0611) (10027.7405 3117.3282) (10057.084 3134.0305) (10030.855 3111.3893)
      (10003.8779 3086.3053) (9977.3588 3059.9695) (9951.5878 3032.8092) (9926.855 3005.2519) (9903.4504 2977.7099)
      (9881.6794 2950.5954) (9861.8473 2924.3511) (9844.2137 2899.374) (9829.0992 2876.1069) (9816.7939 2854.9618)
      (9839.2214 2870.1985) (9863.2519 2887.9389) (9888.5191 2907.9084) (9914.6412 2929.8168) (9941.2214 2953.3435)
      (9967.8626 2978.229) (9994.1985 3004.1679) (10019.8473 3030.8702) (10044.3969 3058.0458) (10066.0305 3083.6947)
      (10061.1145 3074.9771) (10043.4046 3040.8092) (10026.5191 3005.6031) (10010.6107 2969.8626) (9995.8321 2934.0916)
      (9982.3206 2898.8397) (9970.229 2864.5954) (9959.6947 2831.8779) (9950.8702 2801.2061) (9943.9084 2773.1145)
      (9938.9313 2748.0916) (9955.4656 2771.0229) (9972.7176 2796.9924) (9990.458 2825.5725) (10008.3817 2856.3206)
      (10026.2137 2888.8397) (10043.6794 2922.687) (10060.5191 2957.4504) (10076.4427 2992.7023) (10088.7939 3022.3206)
      (10085.6641 3006.7939) (10078.5344 2965.1756) (10072.4885 2923.2977) (10067.5267 2881.7557) (10063.6641 2841.1145)
      (10060.916 2801.9542) (10059.2672 2764.8702) (10058.7481 2730.4122) (10059.3435 2699.1908) (10061.0687 2671.7557)
      (10071.0687 2700.5496) (10080.9771 2732.7176) (10090.6718 2767.7099) (10099.9695 2805.0229) (10108.7176 2844.1374)
      (10116.7786 2884.5344) (10123.9847 2925.6641) (10130.1832 2967.0382) (10135.2061 3008.1221) (10138.916 3048.3817)
      (10141.145 3087.2977) (10141.7405 3124.3664) (10140.5496 3159.0534) (10137.4046 3190.8397) (10103.9237 3195.6489)
      (10067.6489 3198.7023) (10029.145 3200.1221) (9988.9618 3200.0458) (9947.6641 3198.6107) (9905.8015 3195.9237)
      (9863.9542 3192.1221) (9822.687 3187.3282) (9782.5344 3181.6794) (9744.0611 3175.2977) (9707.8626 3168.3206)
      (9674.458 3160.8702) (9644.4275 3153.0687)
    ))
    ; P3227 -- see feature_dimensions_mm.csv
    ("06_ORNAMENT" 1 (
      (9619.9389 5447.3282) (9621.145 5442.7939) (9624.4733 5439.4809) (9629.0076 5438.2595) (9633.542 5439.4809)
      (9636.855 5442.7939) (9638.0763 5447.3282) (9636.855 5451.8626) (9633.542 5455.1908) (9629.0076 5456.3969)
      (9624.4733 5455.1908) (9621.145 5451.8626)
    ))
    ; P3228 -- see feature_dimensions_mm.csv
    ("06_ORNAMENT" 1 (
      (9619.9389 5148.0763) (9621.145 5143.542) (9624.4733 5140.229) (9629.0076 5139.0076) (9633.542 5140.229)
      (9636.855 5143.542) (9638.0763 5148.0763) (9636.855 5152.6107) (9633.542 5155.9389) (9629.0076 5157.145)
      (9624.4733 5155.9389) (9621.145 5152.6107)
    ))
    ; P3229 -- see feature_dimensions_mm.csv
    ("06_ORNAMENT" 1 (
      (9619.9389 4851.9084) (9621.145 4847.374) (9624.4733 4844.0611) (9629.0076 4842.8397) (9633.542 4844.0611)
      (9636.855 4847.374) (9638.0763 4851.9084) (9636.855 4856.4427) (9633.542 4859.771) (9629.0076 4860.9771)
      (9624.4733 4859.771) (9621.145 4856.4427)
    ))
    ; P3230 -- see feature_dimensions_mm.csv
    ("06_ORNAMENT" 1 (
      (9619.9389 4552.6565) (9621.145 4548.1221) (9624.4733 4544.8092) (9629.0076 4543.5878) (9633.542 4544.8092)
      (9636.855 4548.1221) (9638.0763 4552.6565) (9636.855 4557.1908) (9633.542 4560.5191) (9629.0076 4561.7252)
      (9624.4733 4560.5191) (9621.145 4557.1908)
    ))
    ; P3231 -- see feature_dimensions_mm.csv
    ("06_ORNAMENT" 1 (
      (9619.9389 4256.4885) (9621.145 4251.9542) (9624.4733 4248.6412) (9629.0076 4247.4198) (9633.542 4248.6412)
      (9636.855 4251.9542) (9638.0763 4256.4885) (9636.855 4261.0229) (9633.542 4264.3511) (9629.0076 4265.5573)
      (9624.4733 4264.3511) (9621.145 4261.0229)
    ))
    ; P3232 -- see feature_dimensions_mm.csv
    ("06_ORNAMENT" 1 (
      (9619.9389 3957.2366) (9621.145 3952.7176) (9624.4733 3949.3893) (9629.0076 3948.1679) (9633.542 3949.3893)
      (9636.855 3952.7176) (9638.0763 3957.2366) (9636.855 3961.771) (9633.542 3965.0992) (9629.0076 3966.3053)
      (9624.4733 3965.0992) (9621.145 3961.771)
    ))
    ; P3233 -- see feature_dimensions_mm.csv
    ("06_ORNAMENT" 1 (
      (9627.4809 5297.7099) (9628.0458 5293.6183) (9629.7557 5289.6183) (9632.5344 5285.8168) (9636.3359 5282.3053)
      (9641.0534 5279.1908) (9646.5802 5276.5191) (9652.7939 5274.3664) (9659.5115 5272.7939) (9666.5802 5271.8321)
      (9673.8321 5271.5115) (9681.084 5271.8321) (9688.1527 5272.7939) (9694.8702 5274.3664) (9701.084 5276.5191)
      (9706.6107 5279.1908) (9711.3282 5282.3053) (9715.1298 5285.8168) (9717.9084 5289.6183) (9719.6183 5293.6183)
      (9720.1832 5297.7099) (9719.6183 5301.8015) (9717.9084 5305.8015) (9715.1298 5309.6031) (9711.3282 5313.1145)
      (9706.6107 5316.229) (9701.084 5318.9008) (9694.8702 5321.0534) (9688.1527 5322.626) (9681.084 5323.5878)
      (9673.8321 5323.9084) (9666.5802 5323.5878) (9659.5115 5322.626) (9652.7939 5321.0534) (9646.5802 5318.9008)
      (9641.0534 5316.229) (9636.3359 5313.1145) (9632.5344 5309.6031) (9629.7557 5305.8015) (9628.0458 5301.8015)
    ))
    ; P3234 -- see feature_dimensions_mm.csv
    ("06_ORNAMENT" 1 (
      (9627.4809 4702.2901) (9628.0458 4698.1985) (9629.7557 4694.1985) (9632.5344 4690.3969) (9636.3359 4686.8855)
      (9641.0534 4683.771) (9646.5802 4681.0992) (9652.7939 4678.9466) (9659.5115 4677.374) (9666.5802 4676.4122)
      (9673.8321 4676.0916) (9681.084 4676.4122) (9688.1527 4677.374) (9694.8702 4678.9466) (9701.084 4681.0992)
      (9706.6107 4683.771) (9711.3282 4686.8855) (9715.1298 4690.3969) (9717.9084 4694.1985) (9719.6183 4698.1985)
      (9720.1832 4702.2901) (9719.6183 4706.3817) (9717.9084 4710.3817) (9715.1298 4714.1832) (9711.3282 4717.6947)
      (9706.6107 4720.8092) (9701.084 4723.4809) (9694.8702 4725.6336) (9688.1527 4727.2061) (9681.084 4728.1679)
      (9673.8321 4728.4885) (9666.5802 4728.1679) (9659.5115 4727.2061) (9652.7939 4725.6336) (9646.5802 4723.4809)
      (9641.0534 4720.8092) (9636.3359 4717.6947) (9632.5344 4714.1832) (9629.7557 4710.3817) (9628.0458 4706.3817)
    ))
    ; P3235 -- see feature_dimensions_mm.csv
    ("06_ORNAMENT" 1 (
      (9627.4809 4106.8702) (9628.0458 4102.7786) (9629.7557 4098.7786) (9632.5344 4094.9771) (9636.3359 4091.4656)
      (9641.0534 4088.3511) (9646.5802 4085.6794) (9652.7939 4083.5267) (9659.5115 4081.9542) (9666.5802 4080.9924)
      (9673.8321 4080.6718) (9681.084 4080.9924) (9688.1527 4081.9542) (9694.8702 4083.5267) (9701.084 4085.6794)
      (9706.6107 4088.3511) (9711.3282 4091.4656) (9715.1298 4094.9771) (9717.9084 4098.7786) (9719.6183 4102.7786)
      (9720.1832 4106.8702) (9719.6183 4110.9618) (9717.9084 4114.9618) (9715.1298 4118.7634) (9711.3282 4122.2748)
      (9706.6107 4125.3893) (9701.084 4128.0611) (9694.8702 4130.2137) (9688.1527 4131.7863) (9681.084 4132.7481)
      (9673.8321 4133.0687) (9666.5802 4132.7481) (9659.5115 4131.7863) (9652.7939 4130.2137) (9646.5802 4128.0611)
      (9641.0534 4125.3893) (9636.3359 4122.2748) (9632.5344 4118.7634) (9629.7557 4114.9618) (9628.0458 4110.9618)
    ))
    ; P3236 -- see feature_dimensions_mm.csv
    ("06_ORNAMENT" 1 (
      (9666.916 5392.5954) (9667.1145 5387.4351) (9668.2443 5381.8931) (9670.2748 5376.0916) (9673.145 5370.1832)
      (9676.7786 5364.3206) (9681.0992 5358.6412) (9686.0 5353.2824) (9691.3588 5348.3817) (9697.0382 5344.0611)
      (9702.9008 5340.4275) (9708.8092 5337.5573) (9714.5954 5335.542) (9720.1527 5334.4122) (9725.313 5334.1985)
      (9729.9695 5334.916) (9734.0 5336.5344) (9737.2977 5339.0382) (9739.8015 5342.3359) (9741.4198 5346.3664)
      (9742.1374 5351.0229) (9741.9237 5356.1832) (9740.7939 5361.7405) (9738.7786 5367.5267) (9735.9084 5373.4351)
      (9732.2748 5379.2977) (9727.9542 5384.9771) (9723.0534 5390.3359) (9717.6947 5395.2366) (9712.0153 5399.5573)
      (9706.1527 5403.1908) (9700.2443 5406.0611) (9694.4427 5408.0916) (9688.9008 5409.2214) (9683.7405 5409.4198)
      (9679.084 5408.7023) (9675.0534 5407.084) (9671.7557 5404.5802) (9669.2519 5401.2824) (9667.6336 5397.2519)
    ))
    ; P3237 -- see feature_dimensions_mm.csv
    ("06_ORNAMENT" 1 (
      (9666.916 5202.8092) (9667.6336 5198.1679) (9669.2519 5194.1374) (9671.7557 5190.8397) (9675.0534 5188.3359)
      (9679.084 5186.7176) (9683.7405 5186.0) (9688.9008 5186.1985) (9694.4427 5187.3282) (9700.2443 5189.3588)
      (9706.1527 5192.229) (9712.0153 5195.8626) (9717.6947 5200.1832) (9723.0534 5205.084) (9727.9542 5210.4427)
      (9732.2748 5216.1221) (9735.9084 5221.9847) (9738.7786 5227.8931) (9740.7939 5233.6794) (9741.9237 5239.2366)
      (9742.1374 5244.3969) (9741.4198 5249.0534) (9739.8015 5253.084) (9737.2977 5256.3817) (9734.0 5258.8855)
      (9729.9695 5260.5038) (9725.313 5261.2214) (9720.1527 5261.0076) (9714.5954 5259.8779) (9708.8092 5257.8626)
      (9702.9008 5254.9924) (9697.0382 5251.3588) (9691.3588 5247.0382) (9686.0 5242.1374) (9681.0992 5236.7786)
      (9676.7786 5231.0992) (9673.145 5225.2366) (9670.2748 5219.3282) (9668.2443 5213.5267) (9667.1145 5207.9847)
    ))
    ; P3238 -- see feature_dimensions_mm.csv
    ("06_ORNAMENT" 1 (
      (9666.916 4797.1756) (9667.1145 4792.0153) (9668.2443 4786.4733) (9670.2748 4780.6718) (9673.145 4774.7634)
      (9676.7786 4768.9008) (9681.0992 4763.2214) (9686.0 4757.8626) (9691.3588 4752.9618) (9697.0382 4748.6412)
      (9702.9008 4745.0076) (9708.8092 4742.1374) (9714.5954 4740.1221) (9720.1527 4738.9924) (9725.313 4738.7786)
      (9729.9695 4739.4962) (9734.0 4741.1145) (9737.2977 4743.6183) (9739.8015 4746.916) (9741.4198 4750.9466)
      (9742.1374 4755.6031) (9741.9237 4760.7634) (9740.7939 4766.3206) (9738.7786 4772.1069) (9735.9084 4778.0153)
      (9732.2748 4783.8779) (9727.9542 4789.5573) (9723.0534 4794.916) (9717.6947 4799.8168) (9712.0153 4804.1374)
      (9706.1527 4807.771) (9700.2443 4810.6412) (9694.4427 4812.6718) (9688.9008 4813.8015) (9683.7405 4814.0)
      (9679.084 4813.2824) (9675.0534 4811.6641) (9671.7557 4809.1603) (9669.2519 4805.8626) (9667.6336 4801.8321)
    ))
    ; P3239 -- see feature_dimensions_mm.csv
    ("06_ORNAMENT" 1 (
      (9666.916 4607.3893) (9667.6336 4602.7481) (9669.2519 4598.7176) (9671.7557 4595.4198) (9675.0534 4592.916)
      (9679.084 4591.2977) (9683.7405 4590.5802) (9688.9008 4590.7786) (9694.4427 4591.9084) (9700.2443 4593.9389)
      (9706.1527 4596.8092) (9712.0153 4600.4427) (9717.6947 4604.7634) (9723.0534 4609.6641) (9727.9542 4615.0229)
      (9732.2748 4620.7023) (9735.9084 4626.5649) (9738.7786 4632.4733) (9740.7939 4638.2595) (9741.9237 4643.8168)
      (9742.1374 4648.9771) (9741.4198 4653.6336) (9739.8015 4657.6641) (9737.2977 4660.9618) (9734.0 4663.4656)
      (9729.9695 4665.084) (9725.313 4665.8015) (9720.1527 4665.5878) (9714.5954 4664.458) (9708.8092 4662.4427)
      (9702.9008 4659.5725) (9697.0382 4655.9389) (9691.3588 4651.6183) (9686.0 4646.7176) (9681.0992 4641.3588)
      (9676.7786 4635.6794) (9673.145 4629.8168) (9670.2748 4623.9084) (9668.2443 4618.1069) (9667.1145 4612.5649)
    ))
    ; P3240 -- see feature_dimensions_mm.csv
    ("06_ORNAMENT" 1 (
      (9666.916 4201.7557) (9667.1145 4196.5954) (9668.2443 4191.0534) (9670.2748 4185.2519) (9673.145 4179.3435)
      (9676.7786 4173.4809) (9681.0992 4167.8015) (9686.0 4162.4427) (9691.3588 4157.542) (9697.0382 4153.2214)
      (9702.9008 4149.5878) (9708.8092 4146.7176) (9714.5954 4144.7023) (9720.1527 4143.5725) (9725.313 4143.3588)
      (9729.9695 4144.0763) (9734.0 4145.6947) (9737.2977 4148.1985) (9739.8015 4151.4962) (9741.4198 4155.5267)
      (9742.1374 4160.1832) (9741.9237 4165.3435) (9740.7939 4170.9008) (9738.7786 4176.687) (9735.9084 4182.5954)
      (9732.2748 4188.458) (9727.9542 4194.1374) (9723.0534 4199.4962) (9717.6947 4204.3969) (9712.0153 4208.7176)
      (9706.1527 4212.3511) (9700.2443 4215.2214) (9694.4427 4217.2519) (9688.9008 4218.3817) (9683.7405 4218.5802)
      (9679.084 4217.8626) (9675.0534 4216.2443) (9671.7557 4213.7405) (9669.2519 4210.4427) (9667.6336 4206.4122)
    ))
    ; P3241 -- see feature_dimensions_mm.csv
    ("06_ORNAMENT" 1 (
      (9666.916 4011.9695) (9667.6336 4007.3282) (9669.2519 4003.2977) (9671.7557 4000.0) (9675.0534 3997.4962)
      (9679.084 3995.8779) (9683.7405 3995.1603) (9688.9008 3995.3588) (9694.4427 3996.4885) (9700.2443 3998.5191)
      (9706.1527 4001.3893) (9712.0153 4005.0229) (9717.6947 4009.3435) (9723.0534 4014.2443) (9727.9542 4019.6031)
      (9732.2748 4025.2824) (9735.9084 4031.145) (9738.7786 4037.0534) (9740.7939 4042.8397) (9741.9237 4048.3969)
      (9742.1374 4053.5573) (9741.4198 4058.2137) (9739.8015 4062.2443) (9737.2977 4065.542) (9734.0 4068.0458)
      (9729.9695 4069.6641) (9725.313 4070.3817) (9720.1527 4070.1679) (9714.5954 4069.0382) (9708.8092 4067.0229)
      (9702.9008 4064.1527) (9697.0382 4060.5191) (9691.3588 4056.1985) (9686.0 4051.2977) (9681.0992 4045.9389)
      (9676.7786 4040.2595) (9673.145 4034.3969) (9670.2748 4028.4885) (9668.2443 4022.687) (9667.1145 4017.145)
    ))
    ; P3242 -- see feature_dimensions_mm.csv
    ("06_ORNAMENT" 1 (
      (9688.5802 5102.2137) (9689.8015 5097.6794) (9693.1145 5094.3664) (9697.6489 5093.145) (9702.1832 5094.3664)
      (9705.4962 5097.6794) (9706.7176 5102.2137) (9705.4962 5106.7481) (9702.1832 5110.0611) (9697.6489 5111.2824)
      (9693.1145 5110.0611) (9689.8015 5106.7481)
    ))
    ; P3243 -- see feature_dimensions_mm.csv
    ("06_ORNAMENT" 1 (
      (9688.5802 4897.7863) (9689.8015 4893.2519) (9693.1145 4889.9389) (9697.6489 4888.7176) (9702.1832 4889.9389)
      (9705.4962 4893.2519) (9706.7176 4897.7863) (9705.4962 4902.3206) (9702.1832 4905.6336) (9697.6489 4906.855)
      (9693.1145 4905.6336) (9689.8015 4902.3206)
    ))
    ; P3244 -- see feature_dimensions_mm.csv
    ("06_ORNAMENT" 1 (
      (9688.5802 4506.7939) (9689.8015 4502.2595) (9693.1145 4498.9466) (9697.6489 4497.7252) (9702.1832 4498.9466)
      (9705.4962 4502.2595) (9706.7176 4506.7939) (9705.4962 4511.3282) (9702.1832 4514.6412) (9697.6489 4515.8626)
      (9693.1145 4514.6412) (9689.8015 4511.3282)
    ))
    ; P3245 -- see feature_dimensions_mm.csv
    ("06_ORNAMENT" 1 (
      (9688.5802 4302.3664) (9689.8015 4297.8321) (9693.1145 4294.5191) (9697.6489 4293.2977) (9702.1832 4294.5191)
      (9705.4962 4297.8321) (9706.7176 4302.3664) (9705.4962 4306.9008) (9702.1832 4310.2137) (9697.6489 4311.4351)
      (9693.1145 4310.2137) (9689.8015 4306.9008)
    ))
    ; P3246 -- see feature_dimensions_mm.csv
    ("06_ORNAMENT" 1 (
      (9688.5802 3911.374) (9689.8015 3906.8397) (9693.1145 3903.5267) (9697.6489 3902.3053) (9702.1832 3903.5267)
      (9705.4962 3906.8397) (9706.7176 3911.374) (9705.4962 3915.9084) (9702.1832 3919.2214) (9697.6489 3920.4427)
      (9693.1145 3919.2214) (9689.8015 3915.9084)
    ))
    ; P3247 -- see feature_dimensions_mm.csv
    ("06_ORNAMENT" 1 (
      (9693.6947 5141.313) (9694.6718 5135.084) (9697.542 5129.4656) (9702.0 5125.0076) (9707.6183 5122.1527)
      (9713.8473 5121.1603) (9720.0763 5122.1527) (9725.6947 5125.0076) (9730.1527 5129.4656) (9733.0076 5135.084)
      (9734.0 5141.313) (9733.0076 5147.542) (9730.1527 5153.1603) (9725.6947 5157.6183) (9720.0763 5160.4733)
      (9713.8473 5161.4656) (9707.6183 5160.4733) (9702.0 5157.6183) (9697.542 5153.1603) (9694.6718 5147.542)
    ))
    ; P3248 -- see feature_dimensions_mm.csv
    ("06_ORNAMENT" 1 (
      (9693.6947 4858.687) (9694.6718 4852.458) (9697.542 4846.8397) (9702.0 4842.3817) (9707.6183 4839.5267)
      (9713.8473 4838.5344) (9720.0763 4839.5267) (9725.6947 4842.3817) (9730.1527 4846.8397) (9733.0076 4852.458)
      (9734.0 4858.687) (9733.0076 4864.916) (9730.1527 4870.5344) (9725.6947 4874.9924) (9720.0763 4877.8473)
      (9713.8473 4878.8397) (9707.6183 4877.8473) (9702.0 4874.9924) (9697.542 4870.5344) (9694.6718 4864.916)
    ))
    ; P3249 -- see feature_dimensions_mm.csv
    ("06_ORNAMENT" 1 (
      (9693.6947 4545.8931) (9694.6718 4539.6641) (9697.542 4534.0458) (9702.0 4529.5878) (9707.6183 4526.7328)
      (9713.8473 4525.7405) (9720.0763 4526.7328) (9725.6947 4529.5878) (9730.1527 4534.0458) (9733.0076 4539.6641)
      (9734.0 4545.8931) (9733.0076 4552.1221) (9730.1527 4557.7405) (9725.6947 4562.1985) (9720.0763 4565.0534)
      (9713.8473 4566.0458) (9707.6183 4565.0534) (9702.0 4562.1985) (9697.542 4557.7405) (9694.6718 4552.1221)
    ))
    ; P3250 -- see feature_dimensions_mm.csv
    ("06_ORNAMENT" 1 (
      (9693.6947 4263.2672) (9694.6718 4257.0382) (9697.542 4251.4198) (9702.0 4246.9618) (9707.6183 4244.1069)
      (9713.8473 4243.1145) (9720.0763 4244.1069) (9725.6947 4246.9618) (9730.1527 4251.4198) (9733.0076 4257.0382)
      (9734.0 4263.2672) (9733.0076 4269.4962) (9730.1527 4275.1145) (9725.6947 4279.5725) (9720.0763 4282.4275)
      (9713.8473 4283.4198) (9707.6183 4282.4275) (9702.0 4279.5725) (9697.542 4275.1145) (9694.6718 4269.4962)
    ))
    ; P3251 -- see feature_dimensions_mm.csv
    ("06_ORNAMENT" 1 (
      (9693.6947 3950.4733) (9694.6718 3944.2443) (9697.542 3938.626) (9702.0 3934.1679) (9707.6183 3931.313)
      (9713.8473 3930.3206) (9720.0763 3931.313) (9725.6947 3934.1679) (9730.1527 3938.626) (9733.0076 3944.2443)
      (9734.0 3950.4733) (9733.0076 3956.7023) (9730.1527 3962.3206) (9725.6947 3966.7786) (9720.0763 3969.6336)
      (9713.8473 3970.626) (9707.6183 3969.6336) (9702.0 3966.7786) (9697.542 3962.3206) (9694.6718 3956.7023)
    ))
    ; P3252 -- see feature_dimensions_mm.csv
    ("06_ORNAMENT" 1 (
      (9730.2595 5297.7099) (9731.1908 5288.2748) (9733.9389 5279.2061) (9738.4122 5270.8397) (9744.4275 5263.5115)
      (9751.7557 5257.4962) (9760.1221 5253.0229) (9769.1908 5250.2748) (9778.626 5249.3435) (9788.0611 5250.2748)
      (9797.1298 5253.0229) (9805.4962 5257.4962) (9812.8244 5263.5115) (9818.8397 5270.8397) (9823.313 5279.2061)
      (9826.0611 5288.2748) (9826.9924 5297.7099) (9826.0611 5307.145) (9823.313 5316.2137) (9818.8397 5324.5802)
      (9812.8244 5331.9084) (9805.4962 5337.9237) (9797.1298 5342.3969) (9788.0611 5345.145) (9778.626 5346.0763)
      (9769.1908 5345.145) (9760.1221 5342.3969) (9751.7557 5337.9237) (9744.4275 5331.9084) (9738.4122 5324.5802)
      (9733.9389 5316.2137) (9731.1908 5307.145)
    ))
    ; P3253 -- see feature_dimensions_mm.csv
    ("06_ORNAMENT" 1 (
      (9730.2595 4702.2901) (9731.1908 4692.855) (9733.9389 4683.7863) (9738.4122 4675.4198) (9744.4275 4668.0916)
      (9751.7557 4662.0763) (9760.1221 4657.6031) (9769.1908 4654.855) (9778.626 4653.9237) (9788.0611 4654.855)
      (9797.1298 4657.6031) (9805.4962 4662.0763) (9812.8244 4668.0916) (9818.8397 4675.4198) (9823.313 4683.7863)
      (9826.0611 4692.855) (9826.9924 4702.2901) (9826.0611 4711.7252) (9823.313 4720.7939) (9818.8397 4729.1603)
      (9812.8244 4736.4885) (9805.4962 4742.5038) (9797.1298 4746.9771) (9788.0611 4749.7252) (9778.626 4750.6565)
      (9769.1908 4749.7252) (9760.1221 4746.9771) (9751.7557 4742.5038) (9744.4275 4736.4885) (9738.4122 4729.1603)
      (9733.9389 4720.7939) (9731.1908 4711.7252)
    ))
    ; P3254 -- see feature_dimensions_mm.csv
    ("06_ORNAMENT" 1 (
      (9730.2595 4106.8702) (9731.1908 4097.4351) (9733.9389 4088.3664) (9738.4122 4080.0) (9744.4275 4072.6718)
      (9751.7557 4066.6565) (9760.1221 4062.1832) (9769.1908 4059.4351) (9778.626 4058.5038) (9788.0611 4059.4351)
      (9797.1298 4062.1832) (9805.4962 4066.6565) (9812.8244 4072.6718) (9818.8397 4080.0) (9823.313 4088.3664)
      (9826.0611 4097.4351) (9826.9924 4106.8702) (9826.0611 4116.3053) (9823.313 4125.374) (9818.8397 4133.7405)
      (9812.8244 4141.0687) (9805.4962 4147.084) (9797.1298 4151.5573) (9788.0611 4154.3053) (9778.626 4155.2366)
      (9769.1908 4154.3053) (9760.1221 4151.5573) (9751.7557 4147.084) (9744.4275 4141.0687) (9738.4122 4133.7405)
      (9733.9389 4125.374) (9731.1908 4116.3053)
    ))
    ; P3255 -- see feature_dimensions_mm.csv
    ("06_ORNAMENT" 1 (
      (9738.9313 5007.6336) (9739.3435 5005.0534) (9740.5344 5002.626) (9742.4275 5000.4275) (9744.8855 4998.5954)
      (9747.7252 4997.145) (9750.7481 4996.0916) (9753.7863 4995.374) (9756.626 4994.9313) (9759.145 4994.6107)
      (9761.2366 4994.2901) (9762.8702 4993.8168) (9764.0305 4993.0382) (9764.8092 4991.8779) (9765.2824 4990.2443)
      (9765.6031 4988.1527) (9765.9237 4985.6336) (9766.3664 4982.7939) (9767.084 4979.7557) (9768.1374 4976.7328)
      (9769.5878 4973.8931) (9771.4198 4971.4351) (9773.6183 4969.542) (9776.0458 4968.3511) (9778.626 4967.9389)
      (9781.2061 4968.3511) (9783.6336 4969.542) (9785.8321 4971.4351) (9787.6641 4973.8931) (9789.1145 4976.7328)
      (9790.1679 4979.7557) (9790.8855 4982.7939) (9791.3282 4985.6336) (9791.6489 4988.1527) (9791.9695 4990.2443)
      (9792.4427 4991.8779) (9793.2214 4993.0382) (9794.3817 4993.8168) (9796.0153 4994.2901) (9798.1069 4994.6107)
      (9800.626 4994.9313) (9803.4656 4995.374) (9806.5038 4996.0916) (9809.5267 4997.145) (9812.3664 4998.5954)
      (9814.8244 5000.4275) (9816.7176 5002.626) (9817.9084 5005.0534) (9818.3206 5007.6336) (9817.9084 5010.2137)
      (9816.7176 5012.6412) (9814.8244 5014.8397) (9812.3664 5016.6718) (9809.5267 5018.1221) (9806.5038 5019.1756)
      (9803.4656 5019.8931) (9800.626 5020.3359) (9798.1069 5020.6565) (9796.0153 5020.9771) (9794.3817 5021.4504)
      (9793.2214 5022.229) (9792.4427 5023.3893) (9791.9695 5025.0229) (9791.6489 5027.1145) (9791.3282 5029.6336)
      (9790.8855 5032.4733) (9790.1679 5035.5115) (9789.1145 5038.5344) (9787.6641 5041.374) (9785.8321 5043.8321)
      (9783.6336 5045.7252) (9781.2061 5046.916) (9778.626 5047.3282) (9776.0458 5046.916) (9773.6183 5045.7252)
      (9771.4198 5043.8321) (9769.5878 5041.374) (9768.1374 5038.5344) (9767.084 5035.5115) (9766.3664 5032.4733)
      (9765.9237 5029.6336) (9765.6031 5027.1145) (9765.2824 5025.0229) (9764.8092 5023.3893) (9764.0305 5022.229)
      (9762.8702 5021.4504) (9761.2366 5020.9771) (9759.145 5020.6565) (9756.626 5020.3359) (9753.7863 5019.8931)
      (9750.7481 5019.1756) (9747.7252 5018.1221) (9744.8855 5016.6718) (9742.4275 5014.8397) (9740.5344 5012.6412)
      (9739.3435 5010.2137)
    ))
    ; P3256 -- see feature_dimensions_mm.csv
    ("06_ORNAMENT" 1 (
      (9738.9313 4412.2137) (9739.3435 4409.6336) (9740.5344 4407.2061) (9742.4275 4405.0076) (9744.8855 4403.1756)
      (9747.7252 4401.7252) (9750.7481 4400.6718) (9753.7863 4399.9542) (9756.626 4399.5115) (9759.145 4399.1908)
      (9761.2366 4398.8702) (9762.8702 4398.3969) (9764.0305 4397.6183) (9764.8092 4396.458) (9765.2824 4394.8244)
      (9765.6031 4392.7328) (9765.9237 4390.2137) (9766.3664 4387.374) (9767.084 4384.3359) (9768.1374 4381.313)
      (9769.5878 4378.4733) (9771.4198 4376.0153) (9773.6183 4374.1221) (9776.0458 4372.9313) (9778.626 4372.5191)
      (9781.2061 4372.9313) (9783.6336 4374.1221) (9785.8321 4376.0153) (9787.6641 4378.4733) (9789.1145 4381.313)
      (9790.1679 4384.3359) (9790.8855 4387.374) (9791.3282 4390.2137) (9791.6489 4392.7328) (9791.9695 4394.8244)
      (9792.4427 4396.458) (9793.2214 4397.6183) (9794.3817 4398.3969) (9796.0153 4398.8702) (9798.1069 4399.1908)
      (9800.626 4399.5115) (9803.4656 4399.9542) (9806.5038 4400.6718) (9809.5267 4401.7252) (9812.3664 4403.1756)
      (9814.8244 4405.0076) (9816.7176 4407.2061) (9817.9084 4409.6336) (9818.3206 4412.2137)
    ))
    ; P3257 -- see feature_dimensions_mm.csv
    ("06_ORNAMENT" 1 (
      (9750.4122 5297.7099) (9751.374 5290.4122) (9754.1985 5283.6031) (9758.6718 5277.7557) (9764.5191 5273.2824)
      (9771.3282 5270.458) (9778.626 5269.4962) (9785.9237 5270.458) (9792.7328 5273.2824) (9798.5802 5277.7557)
      (9803.0534 5283.6031) (9805.8779 5290.4122) (9806.8397 5297.7099) (9805.8779 5305.0076) (9803.0534 5311.8168)
      (9798.5802 5317.6641) (9792.7328 5322.1374) (9785.9237 5324.9618) (9778.626 5325.9237) (9771.3282 5324.9618)
      (9764.5191 5322.1374) (9758.6718 5317.6641) (9754.1985 5311.8168) (9751.374 5305.0076)
    ))
    ; P3258 -- see feature_dimensions_mm.csv
    ("06_ORNAMENT" 1 (
      (9750.4122 4702.2901) (9751.374 4694.9924) (9754.1985 4688.1832) (9758.6718 4682.3359) (9764.5191 4677.8626)
      (9771.3282 4675.0382) (9778.626 4674.0763) (9785.9237 4675.0382) (9792.7328 4677.8626) (9798.5802 4682.3359)
      (9803.0534 4688.1832) (9805.8779 4694.9924) (9806.8397 4702.2901) (9805.8779 4709.5878) (9803.0534 4716.3969)
      (9798.5802 4722.2443) (9792.7328 4726.7176) (9785.9237 4729.542) (9778.626 4730.5038) (9771.3282 4729.542)
      (9764.5191 4726.7176) (9758.6718 4722.2443) (9754.1985 4716.3969) (9751.374 4709.5878)
    ))
    ; P3259 -- see feature_dimensions_mm.csv
    ("06_ORNAMENT" 1 (
      (9750.4122 4106.8702) (9751.374 4099.5725) (9754.1985 4092.7634) (9758.6718 4086.916) (9764.5191 4082.4427)
      (9771.3282 4079.6183) (9778.626 4078.6565) (9785.9237 4079.6183) (9792.7328 4082.4427) (9798.5802 4086.916)
      (9803.0534 4092.7634) (9805.8779 4099.5725) (9806.8397 4106.8702) (9805.8779 4114.1679) (9803.0534 4120.9771)
      (9798.5802 4126.8244) (9792.7328 4131.2977) (9785.9237 4134.1221) (9778.626 4135.084) (9771.3282 4134.1221)
      (9764.5191 4131.2977) (9758.6718 4126.8244) (9754.1985 4120.9771) (9751.374 4114.1679)
    ))
    ; P3260 -- see feature_dimensions_mm.csv
    ("06_ORNAMENT" 1 (
      (9752.4275 5192.916) (9752.7481 5185.6641) (9753.7099 5178.5954) (9755.2824 5171.8779) (9757.4351 5165.6641)
      (9760.1069 5160.1374) (9763.2214 5155.4198) (9766.7328 5151.6183) (9770.5344 5148.8397) (9774.5344 5147.1298)
      (9778.626 5146.5649) (9782.7176 5147.1298) (9786.7176 5148.8397) (9790.5191 5151.6183) (9794.0305 5155.4198)
      (9797.145 5160.1374) (9799.8168 5165.6641) (9801.9695 5171.8779) (9803.542 5178.5954) (9804.5038 5185.6641)
      (9804.8244 5192.916) (9804.5038 5200.1679) (9803.542 5207.2366) (9801.9695 5213.9542) (9799.8168 5220.1679)
      (9797.145 5225.6947) (9794.0305 5230.4122) (9790.5191 5234.2137) (9786.7176 5236.9924) (9782.7176 5238.7023)
      (9778.626 5239.2672) (9774.5344 5238.7023) (9770.5344 5236.9924) (9766.7328 5234.2137) (9763.2214 5230.4122)
      (9760.1069 5225.6947) (9757.4351 5220.1679) (9755.2824 5213.9542) (9753.7099 5207.2366) (9752.7481 5200.1679)
    ))
    ; P3261 -- see feature_dimensions_mm.csv
    ("06_ORNAMENT" 1 (
      (9752.4275 4807.084) (9752.7481 4799.8321) (9753.7099 4792.7634) (9755.2824 4786.0458) (9757.4351 4779.8321)
      (9760.1069 4774.3053) (9763.2214 4769.5878) (9766.7328 4765.7863) (9770.5344 4763.0076) (9774.5344 4761.2977)
      (9778.626 4760.7328) (9782.7176 4761.2977) (9786.7176 4763.0076) (9790.5191 4765.7863) (9794.0305 4769.5878)
      (9797.145 4774.3053) (9799.8168 4779.8321) (9801.9695 4786.0458) (9803.542 4792.7634) (9804.5038 4799.8321)
      (9804.8244 4807.084) (9804.5038 4814.3359) (9803.542 4821.4046) (9801.9695 4828.1221) (9799.8168 4834.3359)
      (9797.145 4839.8626) (9794.0305 4844.5802) (9790.5191 4848.3817) (9786.7176 4851.1603) (9782.7176 4852.8702)
      (9778.626 4853.4351) (9774.5344 4852.8702) (9770.5344 4851.1603) (9766.7328 4848.3817) (9763.2214 4844.5802)
      (9760.1069 4839.8626) (9757.4351 4834.3359) (9755.2824 4828.1221) (9753.7099 4821.4046) (9752.7481 4814.3359)
    ))
    ; P3262 -- see feature_dimensions_mm.csv
    ("06_ORNAMENT" 1 (
      (9752.4275 4597.4962) (9752.7481 4590.2443) (9753.7099 4583.1756) (9755.2824 4576.458) (9757.4351 4570.2443)
      (9760.1069 4564.7176) (9763.2214 4560.0) (9766.7328 4556.1985) (9770.5344 4553.4198) (9774.5344 4551.7099)
      (9778.626 4551.145) (9782.7176 4551.7099) (9786.7176 4553.4198) (9790.5191 4556.1985) (9794.0305 4560.0)
      (9797.145 4564.7176) (9799.8168 4570.2443) (9801.9695 4576.458) (9803.542 4583.1756) (9804.5038 4590.2443)
      (9804.8244 4597.4962) (9804.5038 4604.7481) (9803.542 4611.8168) (9801.9695 4618.5344) (9799.8168 4624.7481)
      (9797.145 4630.2748) (9794.0305 4634.9924) (9790.5191 4638.7939) (9786.7176 4641.5725) (9782.7176 4643.2824)
      (9778.626 4643.8473) (9774.5344 4643.2824) (9770.5344 4641.5725) (9766.7328 4638.7939) (9763.2214 4634.9924)
      (9760.1069 4630.2748) (9757.4351 4624.7481) (9755.2824 4618.5344) (9753.7099 4611.8168) (9752.7481 4604.7481)
    ))
    ; P3263 -- see feature_dimensions_mm.csv
    ("06_ORNAMENT" 1 (
      (9752.4275 4211.6641) (9752.7481 4204.4122) (9753.7099 4197.3435) (9755.2824 4190.626) (9757.4351 4184.4122)
      (9760.1069 4178.8855) (9763.2214 4174.1679) (9766.7328 4170.3664) (9770.5344 4167.5878) (9774.5344 4165.8779)
      (9778.626 4165.313) (9782.7176 4165.8779) (9786.7176 4167.5878) (9790.5191 4170.3664) (9794.0305 4174.1679)
      (9797.145 4178.8855) (9799.8168 4184.4122) (9801.9695 4190.626) (9803.542 4197.3435) (9804.5038 4204.4122)
      (9804.8244 4211.6641) (9804.5038 4218.916) (9803.542 4225.9847) (9801.9695 4232.7023) (9799.8168 4238.916)
      (9797.145 4244.4427) (9794.0305 4249.1603) (9790.5191 4252.9618) (9786.7176 4255.7405) (9782.7176 4257.4504)
      (9778.626 4258.0153) (9774.5344 4257.4504) (9770.5344 4255.7405) (9766.7328 4252.9618) (9763.2214 4249.1603)
      (9760.1069 4244.4427) (9757.4351 4238.916) (9755.2824 4232.7023) (9753.7099 4225.9847) (9752.7481 4218.916)
    ))
    ; P3264 -- see feature_dimensions_mm.csv
    ("06_ORNAMENT" 1 (
      (9752.4275 4002.0763) (9752.7481 3994.8244) (9753.7099 3987.7557) (9755.2824 3981.0382) (9757.4351 3974.8244)
      (9760.1069 3969.2977) (9763.2214 3964.5802) (9766.7328 3960.7786) (9770.5344 3958.0) (9774.5344 3956.2901)
      (9778.626 3955.7252) (9782.7176 3956.2901) (9786.7176 3958.0) (9790.5191 3960.7786) (9794.0305 3964.5802)
      (9797.145 3969.2977) (9799.8168 3974.8244) (9801.9695 3981.0382) (9803.542 3987.7557) (9804.5038 3994.8244)
      (9804.8244 4002.0763) (9804.5038 4009.3282) (9803.542 4016.3969) (9801.9695 4023.1145) (9799.8168 4029.3282)
      (9797.145 4034.855) (9794.0305 4039.5725) (9790.5191 4043.374) (9786.7176 4046.1527) (9782.7176 4047.8626)
      (9778.626 4048.4275) (9774.5344 4047.8626) (9770.5344 4046.1527) (9766.7328 4043.374) (9763.2214 4039.5725)
      (9760.1069 4034.855) (9757.4351 4029.3282) (9755.2824 4023.1145) (9753.7099 4016.3969) (9752.7481 4009.3282)
    ))
    ; P3265 -- see feature_dimensions_mm.csv
    ("06_ORNAMENT" 1 (
      (9769.5573 5086.1069) (9770.7786 5081.5725) (9774.0916 5078.2595) (9778.626 5077.0382) (9783.1603 5078.2595)
      (9786.4733 5081.5725) (9787.6947 5086.1069) (9786.4733 5090.6412) (9783.1603 5093.9542) (9778.626 5095.1756)
      (9774.0916 5093.9542) (9770.7786 5090.6412)
    ))
    ; P3266 -- see feature_dimensions_mm.csv
    ("06_ORNAMENT" 1 (
      (9769.5573 4913.8931) (9770.7786 4909.3588) (9774.0916 4906.0458) (9778.626 4904.8244) (9783.1603 4906.0458)
      (9786.4733 4909.3588) (9787.6947 4913.8931) (9786.4733 4918.4275) (9783.1603 4921.7405) (9778.626 4922.9618)
      (9774.0916 4921.7405) (9770.7786 4918.4275)
    ))
    ; P3267 -- see feature_dimensions_mm.csv
    ("06_ORNAMENT" 1 (
      (9769.5573 4490.687) (9770.7786 4486.1527) (9774.0916 4482.8397) (9778.626 4481.6183) (9783.1603 4482.8397)
      (9786.4733 4486.1527) (9787.6947 4490.687) (9786.4733 4495.2214) (9783.1603 4498.5344) (9778.626 4499.7557)
      (9774.0916 4498.5344) (9770.7786 4495.2214)
    ))
    ; P3268 -- see feature_dimensions_mm.csv
    ("06_ORNAMENT" 1 (
      (9769.5573 4318.4733) (9770.7786 4313.9389) (9774.0916 4310.626) (9778.626 4309.4046) (9783.1603 4310.626)
      (9786.4733 4313.9389) (9787.6947 4318.4733) (9786.4733 4323.0076) (9783.1603 4326.3206) (9778.626 4327.542)
      (9774.0916 4326.3206) (9770.7786 4323.0076)
    ))
    ; P3269 -- see feature_dimensions_mm.csv
    ("06_ORNAMENT" 1 (
      (9769.5573 3895.2672) (9770.7786 3890.7328) (9774.0916 3887.4198) (9778.626 3886.1985) (9783.1603 3887.4198)
      (9786.4733 3890.7328) (9787.6947 3895.2672) (9786.4733 3899.8015) (9783.1603 3903.1145) (9778.626 3904.3359)
      (9774.0916 3903.1145) (9770.7786 3899.8015)
    ))
    ; P3270 -- see feature_dimensions_mm.csv
    ("06_ORNAMENT" 1 (
      (9815.1145 5244.3969) (9815.3282 5239.2366) (9816.458 5233.6794) (9818.4733 5227.8931) (9821.3435 5221.9847)
      (9824.9771 5216.1221) (9829.2977 5210.4427) (9834.1985 5205.084) (9839.5573 5200.1832) (9845.2366 5195.8626)
      (9851.0992 5192.229) (9857.0076 5189.3588) (9862.8092 5187.3282) (9868.3511 5186.1985) (9873.5267 5186.0)
      (9878.1679 5186.7176) (9882.1985 5188.3359) (9885.4962 5190.8397) (9888.0 5194.1374) (9889.6183 5198.1679)
      (9890.3359 5202.8092) (9890.1374 5207.9847) (9889.0076 5213.5267) (9886.9771 5219.3282) (9884.1069 5225.2366)
      (9880.4733 5231.0992) (9876.1527 5236.7786) (9871.2519 5242.1374) (9865.8931 5247.0382) (9860.2137 5251.3588)
      (9854.3511 5254.9924) (9848.4427 5257.8626) (9842.6565 5259.8779) (9837.0992 5261.0076) (9831.9389 5261.2214)
      (9827.2824 5260.5038) (9823.2519 5258.8855) (9819.9542 5256.3817) (9817.4504 5253.084) (9815.8321 5249.0534)
    ))
    ; P3271 -- see feature_dimensions_mm.csv
    ("06_ORNAMENT" 1 (
      (9815.1145 4755.6031) (9815.8321 4750.9466) (9817.4504 4746.916) (9819.9542 4743.6183) (9823.2519 4741.1145)
      (9827.2824 4739.4962) (9831.9389 4738.7786) (9837.0992 4738.9924) (9842.6565 4740.1221) (9848.4427 4742.1374)
      (9854.3511 4745.0076) (9860.2137 4748.6412) (9865.8931 4752.9618) (9871.2519 4757.8626) (9876.1527 4763.2214)
      (9880.4733 4768.9008) (9884.1069 4774.7634) (9886.9771 4780.6718) (9889.0076 4786.4733) (9890.1374 4792.0153)
      (9890.3359 4797.1756) (9889.6183 4801.8321) (9888.0 4805.8626) (9885.4962 4809.1603) (9882.1985 4811.6641)
      (9878.1679 4813.2824) (9873.5267 4814.0) (9868.3511 4813.8015) (9862.8092 4812.6718) (9857.0076 4810.6412)
      (9851.0992 4807.771) (9845.2366 4804.1374) (9839.5573 4799.8168) (9834.1985 4794.916) (9829.2977 4789.5573)
      (9824.9771 4783.8779) (9821.3435 4778.0153) (9818.4733 4772.1069) (9816.458 4766.3206) (9815.3282 4760.7634)
    ))
    ; P3272 -- see feature_dimensions_mm.csv
    ("06_ORNAMENT" 1 (
      (9815.1145 4648.9771) (9815.3282 4643.8168) (9816.458 4638.2595) (9818.4733 4632.4733) (9821.3435 4626.5649)
      (9824.9771 4620.7023) (9829.2977 4615.0229) (9834.1985 4609.6641) (9839.5573 4604.7634) (9845.2366 4600.4427)
      (9851.0992 4596.8092) (9857.0076 4593.9389) (9862.8092 4591.9084) (9868.3511 4590.7786) (9873.5267 4590.5802)
      (9878.1679 4591.2977) (9882.1985 4592.916) (9885.4962 4595.4198) (9888.0 4598.7176) (9889.6183 4602.7481)
      (9890.3359 4607.3893) (9890.1374 4612.5649) (9889.0076 4618.1069) (9886.9771 4623.9084) (9884.1069 4629.8168)
      (9880.4733 4635.6794) (9876.1527 4641.3588) (9871.2519 4646.7176) (9865.8931 4651.6183) (9860.2137 4655.9389)
      (9854.3511 4659.5725) (9848.4427 4662.4427) (9842.6565 4664.458) (9837.0992 4665.5878) (9831.9389 4665.8015)
      (9827.2824 4665.084) (9823.2519 4663.4656) (9819.9542 4660.9618) (9817.4504 4657.6641) (9815.8321 4653.6336)
    ))
    ; P3273 -- see feature_dimensions_mm.csv
    ("06_ORNAMENT" 1 (
      (9815.1145 4160.1832) (9815.8321 4155.5267) (9817.4504 4151.4962) (9819.9542 4148.1985) (9823.2519 4145.6947)
      (9827.2824 4144.0763) (9831.9389 4143.3588) (9837.0992 4143.5725) (9842.6565 4144.7023) (9848.4427 4146.7176)
      (9854.3511 4149.5878) (9860.2137 4153.2214) (9865.8931 4157.542) (9871.2519 4162.4427) (9876.1527 4167.8015)
      (9880.4733 4173.4809) (9884.1069 4179.3435) (9886.9771 4185.2519) (9889.0076 4191.0534) (9890.1374 4196.5954)
      (9890.3359 4201.7557) (9889.6183 4206.4122) (9888.0 4210.4427) (9885.4962 4213.7405) (9882.1985 4216.2443)
      (9878.1679 4217.8626) (9873.5267 4218.5802) (9868.3511 4218.3817) (9862.8092 4217.2519) (9857.0076 4215.2214)
      (9851.0992 4212.3511) (9845.2366 4208.7176) (9839.5573 4204.3969) (9834.1985 4199.4962) (9829.2977 4194.1374)
      (9824.9771 4188.458) (9821.3435 4182.5954) (9818.4733 4176.687) (9816.458 4170.9008) (9815.3282 4165.3435)
    ))
    ; P3274 -- see feature_dimensions_mm.csv
    ("06_ORNAMENT" 1 (
      (9815.1145 4053.5573) (9815.3282 4048.3969) (9816.458 4042.8397) (9818.4733 4037.0534) (9821.3435 4031.145)
      (9824.9771 4025.2824) (9829.2977 4019.6031) (9834.1985 4014.2443) (9839.5573 4009.3435) (9845.2366 4005.0229)
      (9851.0992 4001.3893) (9857.0076 3998.5191) (9862.8092 3996.4885) (9868.3511 3995.3588) (9873.5267 3995.1603)
      (9878.1679 3995.8779) (9882.1985 3997.4962) (9885.4962 4000.0) (9888.0 4003.2977) (9889.6183 4007.3282)
      (9890.3359 4011.9695) (9890.1374 4017.145) (9889.0076 4022.687) (9886.9771 4028.4885) (9884.1069 4034.3969)
      (9880.4733 4040.2595) (9876.1527 4045.9389) (9871.2519 4051.2977) (9865.8931 4056.1985) (9860.2137 4060.5191)
      (9854.3511 4064.1527) (9848.4427 4067.0229) (9842.6565 4069.0382) (9837.0992 4070.1679) (9831.9389 4070.3817)
      (9827.2824 4069.6641) (9823.2519 4068.0458) (9819.9542 4065.542) (9817.4504 4062.2443) (9815.8321 4058.2137)
    ))
    ; P3275 -- see feature_dimensions_mm.csv
    ("06_ORNAMENT" 1 (
      (9823.2519 5141.313) (9824.2443 5135.084) (9827.0992 5129.4656) (9831.5573 5125.0076) (9837.1756 5122.1527)
      (9843.4046 5121.1603) (9849.6336 5122.1527) (9855.2519 5125.0076) (9859.7099 5129.4656) (9862.5802 5135.084)
      (9863.5573 5141.313) (9862.5802 5147.542) (9859.7099 5153.1603) (9855.2519 5157.6183) (9849.6336 5160.4733)
      (9843.4046 5161.4656) (9837.1756 5160.4733) (9831.5573 5157.6183) (9827.0992 5153.1603) (9824.2443 5147.542)
    ))
    ; P3276 -- see feature_dimensions_mm.csv
    ("06_ORNAMENT" 1 (
      (9823.2519 4858.687) (9824.2443 4852.458) (9827.0992 4846.8397) (9831.5573 4842.3817) (9837.1756 4839.5267)
      (9843.4046 4838.5344) (9849.6336 4839.5267) (9855.2519 4842.3817) (9859.7099 4846.8397) (9862.5802 4852.458)
      (9863.5573 4858.687) (9862.5802 4864.916) (9859.7099 4870.5344) (9855.2519 4874.9924) (9849.6336 4877.8473)
      (9843.4046 4878.8397) (9837.1756 4877.8473) (9831.5573 4874.9924) (9827.0992 4870.5344) (9824.2443 4864.916)
    ))
    ; P3277 -- see feature_dimensions_mm.csv
    ("06_ORNAMENT" 1 (
      (9823.2519 4545.8931) (9824.2443 4539.6641) (9827.0992 4534.0458) (9831.5573 4529.5878) (9837.1756 4526.7328)
      (9843.4046 4525.7405) (9849.6336 4526.7328) (9855.2519 4529.5878) (9859.7099 4534.0458) (9862.5802 4539.6641)
      (9863.5573 4545.8931) (9862.5802 4552.1221) (9859.7099 4557.7405) (9855.2519 4562.1985) (9849.6336 4565.0534)
      (9843.4046 4566.0458) (9837.1756 4565.0534) (9831.5573 4562.1985) (9827.0992 4557.7405) (9824.2443 4552.1221)
    ))
    ; P3278 -- see feature_dimensions_mm.csv
    ("06_ORNAMENT" 1 (
      (9823.2519 4263.2672) (9824.2443 4257.0382) (9827.0992 4251.4198) (9831.5573 4246.9618) (9837.1756 4244.1069)
      (9843.4046 4243.1145) (9849.6336 4244.1069) (9855.2519 4246.9618) (9859.7099 4251.4198) (9862.5802 4257.0382)
      (9863.5573 4263.2672) (9862.5802 4269.4962) (9859.7099 4275.1145) (9855.2519 4279.5725) (9849.6336 4282.4275)
      (9843.4046 4283.4198) (9837.1756 4282.4275) (9831.5573 4279.5725) (9827.0992 4275.1145) (9824.2443 4269.4962)
    ))
    ; P3279 -- see feature_dimensions_mm.csv
    ("06_ORNAMENT" 1 (
      (9823.2519 3950.4733) (9824.2443 3944.2443) (9827.0992 3938.626) (9831.5573 3934.1679) (9837.1756 3931.313)
      (9843.4046 3930.3206) (9849.6336 3931.313) (9855.2519 3934.1679) (9859.7099 3938.626) (9862.5802 3944.2443)
      (9863.5573 3950.4733) (9862.5802 3956.7023) (9859.7099 3962.3206) (9855.2519 3966.7786) (9849.6336 3969.6336)
      (9843.4046 3970.626) (9837.1756 3969.6336) (9831.5573 3966.7786) (9827.0992 3962.3206) (9824.2443 3956.7023)
    ))
    ; P3280 -- see feature_dimensions_mm.csv
    ("06_ORNAMENT" 1 (
      (9837.0687 5297.7099) (9837.6336 5293.6183) (9839.3435 5289.6183) (9842.1221 5285.8168) (9845.9237 5282.3053)
      (9850.6412 5279.1908) (9856.1679 5276.5191) (9862.3817 5274.3664) (9869.0992 5272.7939) (9876.1679 5271.8321)
      (9883.4198 5271.5115) (9890.6718 5271.8321) (9897.7405 5272.7939) (9904.458 5274.3664) (9910.6718 5276.5191)
      (9916.1985 5279.1908) (9920.916 5282.3053) (9924.7176 5285.8168) (9927.4962 5289.6183) (9929.2061 5293.6183)
      (9929.771 5297.7099) (9929.2061 5301.8015) (9927.4962 5305.8015) (9924.7176 5309.6031) (9920.916 5313.1145)
      (9916.1985 5316.229) (9910.6718 5318.9008) (9904.458 5321.0534) (9897.7405 5322.626) (9890.6718 5323.5878)
      (9883.4198 5323.9084) (9876.1679 5323.5878) (9869.0992 5322.626) (9862.3817 5321.0534) (9856.1679 5318.9008)
      (9850.6412 5316.229) (9845.9237 5313.1145) (9842.1221 5309.6031) (9839.3435 5305.8015) (9837.6336 5301.8015)
    ))
    ; P3281 -- see feature_dimensions_mm.csv
    ("06_ORNAMENT" 1 (
      (9837.0687 4702.2901) (9837.6336 4698.1985) (9839.3435 4694.1985) (9842.1221 4690.3969) (9845.9237 4686.8855)
      (9850.6412 4683.771) (9856.1679 4681.0992) (9862.3817 4678.9466) (9869.0992 4677.374) (9876.1679 4676.4122)
      (9883.4198 4676.0916) (9890.6718 4676.4122) (9897.7405 4677.374) (9904.458 4678.9466) (9910.6718 4681.0992)
      (9916.1985 4683.771) (9920.916 4686.8855) (9924.7176 4690.3969) (9927.4962 4694.1985) (9929.2061 4698.1985)
      (9929.771 4702.2901) (9929.2061 4706.3817) (9927.4962 4710.3817) (9924.7176 4714.1832) (9920.916 4717.6947)
      (9916.1985 4720.8092) (9910.6718 4723.4809) (9904.458 4725.6336) (9897.7405 4727.2061) (9890.6718 4728.1679)
      (9883.4198 4728.4885) (9876.1679 4728.1679) (9869.0992 4727.2061) (9862.3817 4725.6336) (9856.1679 4723.4809)
      (9850.6412 4720.8092) (9845.9237 4717.6947) (9842.1221 4714.1832) (9839.3435 4710.3817) (9837.6336 4706.3817)
    ))
    ; P3282 -- see feature_dimensions_mm.csv
    ("06_ORNAMENT" 1 (
      (9837.0687 4106.8702) (9837.6336 4102.7786) (9839.3435 4098.7786) (9842.1221 4094.9771) (9845.9237 4091.4656)
      (9850.6412 4088.3511) (9856.1679 4085.6794) (9862.3817 4083.5267) (9869.0992 4081.9542) (9876.1679 4080.9924)
      (9883.4198 4080.6718) (9890.6718 4080.9924) (9897.7405 4081.9542) (9904.458 4083.5267) (9910.6718 4085.6794)
      (9916.1985 4088.3511) (9920.916 4091.4656) (9924.7176 4094.9771) (9927.4962 4098.7786) (9929.2061 4102.7786)
      (9929.771 4106.8702) (9929.2061 4110.9618) (9927.4962 4114.9618) (9924.7176 4118.7634) (9920.916 4122.2748)
      (9916.1985 4125.3893) (9910.6718 4128.0611) (9904.458 4130.2137) (9897.7405 4131.7863) (9890.6718 4132.7481)
      (9883.4198 4133.0687) (9876.1679 4132.7481) (9869.0992 4131.7863) (9862.3817 4130.2137) (9856.1679 4128.0611)
      (9850.6412 4125.3893) (9845.9237 4122.2748) (9842.1221 4118.7634) (9839.3435 4114.9618) (9837.6336 4110.9618)
    ))
    ; P3283 -- see feature_dimensions_mm.csv
    ("06_ORNAMENT" 1 (
      (9850.5344 5102.2137) (9851.7557 5097.6794) (9855.0687 5094.3664) (9859.6031 5093.145) (9864.1374 5094.3664)
      (9867.4504 5097.6794) (9868.6718 5102.2137) (9867.4504 5106.7481) (9864.1374 5110.0611) (9859.6031 5111.2824)
      (9855.0687 5110.0611) (9851.7557 5106.7481)
    ))
    ; P3284 -- see feature_dimensions_mm.csv
    ("06_ORNAMENT" 1 (
      (9850.5344 4897.7863) (9851.7557 4893.2519) (9855.0687 4889.9389) (9859.6031 4888.7176) (9864.1374 4889.9389)
      (9867.4504 4893.2519) (9868.6718 4897.7863) (9867.4504 4902.3206) (9864.1374 4905.6336) (9859.6031 4906.855)
      (9855.0687 4905.6336) (9851.7557 4902.3206)
    ))
    ; P3285 -- see feature_dimensions_mm.csv
    ("06_ORNAMENT" 1 (
      (9850.5344 4506.7939) (9851.7557 4502.2595) (9855.0687 4498.9466) (9859.6031 4497.7252) (9864.1374 4498.9466)
      (9867.4504 4502.2595) (9868.6718 4506.7939) (9867.4504 4511.3282) (9864.1374 4514.6412) (9859.6031 4515.8626)
      (9855.0687 4514.6412) (9851.7557 4511.3282)
    ))
    ; P3286 -- see feature_dimensions_mm.csv
    ("06_ORNAMENT" 1 (
      (9850.5344 4302.3664) (9851.7557 4297.8321) (9855.0687 4294.5191) (9859.6031 4293.2977) (9864.1374 4294.5191)
      (9867.4504 4297.8321) (9868.6718 4302.3664) (9867.4504 4306.9008) (9864.1374 4310.2137) (9859.6031 4311.4351)
      (9855.0687 4310.2137) (9851.7557 4306.9008)
    ))
    ; P3287 -- see feature_dimensions_mm.csv
    ("06_ORNAMENT" 1 (
      (9850.5344 3911.374) (9851.7557 3906.8397) (9855.0687 3903.5267) (9859.6031 3902.3053) (9864.1374 3903.5267)
      (9867.4504 3906.8397) (9868.6718 3911.374) (9867.4504 3915.9084) (9864.1374 3919.2214) (9859.6031 3920.4427)
      (9855.0687 3919.2214) (9851.7557 3915.9084)
    ))
    ; P3288 -- see feature_dimensions_mm.csv
    ("06_ORNAMENT" 1 (
      (9868.7023 7389.313) (9870.0611 7386.7939) (9873.771 7384.7481) (9878.8092 7383.4198) (9883.8626 7382.7328)
      (9887.6489 7382.2748) (9889.3282 7381.4198) (9888.7328 7379.6183) (9886.3969 7376.6107) (9883.313 7372.5496)
      (9880.687 7368.0458) (9879.5115 7363.9847) (9880.3359 7361.2519) (9883.0687 7360.4275) (9887.1298 7361.6031)
      (9891.6336 7364.229) (9895.6947 7367.313) (9898.7023 7369.6489) (9900.5038 7370.2443) (9901.3588 7368.5649)
      (9901.8168 7364.7786) (9902.5191 7359.7252) (9903.8321 7354.687) (9905.8779 7350.9771) (9908.3969 7349.6183)
      (9910.916 7350.9771) (9912.9618 7354.687) (9914.2901 7359.7252) (9914.9771 7364.7786) (9915.4351 7368.5649)
      (9916.2901 7370.2443) (9918.0916 7369.6489) (9921.0992 7367.313) (9925.1603 7364.229) (9929.6641 7361.6031)
      (9933.7252 7360.4275) (9936.458 7361.2519) (9937.2824 7363.9847) (9936.1069 7368.0458) (9933.4809 7372.5496)
      (9930.3969 7376.6107) (9928.0611 7379.6183) (9927.4656 7381.4198) (9929.145 7382.2748) (9932.9313 7382.7328)
      (9937.9847 7383.4198) (9943.0229 7384.7481) (9946.7328 7386.7939) (9948.0916 7389.313) (9946.7328 7391.8321)
      (9943.0229 7393.8779) (9937.9847 7395.1908) (9932.9313 7395.8931) (9929.145 7396.3511) (9927.4656 7397.2061)
      (9928.0611 7399.0076) (9930.3969 7402.0153) (9933.4809 7406.0763) (9936.1069 7410.5802) (9937.2824 7414.6412)
      (9936.458 7417.374) (9933.7252 7418.1985) (9929.6641 7417.0229) (9925.1603 7414.3969) (9921.0992 7411.313)
      (9918.0916 7408.9771) (9916.2901 7408.3817) (9915.4351 7410.0611) (9914.9771 7413.8473) (9914.2901 7418.9008)
      (9912.9618 7423.9389) (9910.916 7427.6489) (9908.3969 7429.0076) (9905.8779 7427.6489) (9903.8321 7423.9389)
      (9902.5191 7418.9008) (9901.8168 7413.8473) (9901.3588 7410.0611) (9900.5038 7408.3817) (9898.7023 7408.9771)
      (9895.6947 7411.313) (9891.6336 7414.3969) (9887.1298 7417.0229) (9883.0687 7418.1985) (9880.3359 7417.374)
      (9879.5115 7414.6412) (9880.687 7410.5802) (9883.313 7406.0763) (9886.3969 7402.0153) (9888.7328 7399.0076)
      (9889.3282 7397.2061) (9887.6489 7396.3511) (9883.8626 7395.8931) (9878.8092 7395.1908) (9873.771 7393.8779)
      (9870.0611 7391.8321)
    ))
    ; P3289 -- see feature_dimensions_mm.csv
    ("06_ORNAMENT" 1 (
      (9868.7023 7206.1069) (9870.0611 7203.5878) (9873.771 7201.542) (9878.8092 7200.2137) (9883.8626 7199.5267)
      (9887.6489 7199.0687) (9889.3282 7198.2137) (9888.7328 7196.4122) (9886.3969 7193.4046) (9883.313 7189.3435)
      (9880.687 7184.8397) (9879.5115 7180.7786) (9880.3359 7178.0458) (9883.0687 7177.2214) (9887.1298 7178.3969)
      (9891.6336 7181.0229) (9895.6947 7184.1069) (9898.7023 7186.4427) (9900.5038 7187.0382) (9901.3588 7185.3588)
      (9901.8168 7181.5725) (9902.5191 7176.5191) (9903.8321 7171.4809) (9905.8779 7167.771) (9908.3969 7166.4122)
      (9910.916 7167.771) (9912.9618 7171.4809) (9914.2901 7176.5191) (9914.9771 7181.5725) (9915.4351 7185.3588)
      (9916.2901 7187.0382) (9918.0916 7186.4427) (9921.0992 7184.1069) (9925.1603 7181.0229) (9929.6641 7178.3969)
      (9933.7252 7177.2214) (9936.458 7178.0458) (9937.2824 7180.7786) (9936.1069 7184.8397) (9933.4809 7189.3435)
      (9930.3969 7193.4046) (9928.0611 7196.4122) (9927.4656 7198.2137) (9929.145 7199.0687) (9932.9313 7199.5267)
      (9937.9847 7200.2137) (9943.0229 7201.542) (9946.7328 7203.5878) (9948.0916 7206.1069) (9946.7328 7208.626)
      (9943.0229 7210.6718) (9937.9847 7211.9847) (9932.9313 7212.687) (9929.145 7213.145) (9927.4656 7214.0)
      (9928.0611 7215.8015) (9930.3969 7218.8092) (9933.4809 7222.8702) (9936.1069 7227.374) (9937.2824 7231.4351)
      (9936.458 7234.1679) (9933.7252 7234.9924) (9929.6641 7233.8168) (9925.1603 7231.1908) (9921.0992 7228.1069)
      (9918.0916 7225.771) (9916.2901 7225.1756) (9915.4351 7226.855) (9914.9771 7230.6412) (9914.2901 7235.6947)
      (9912.9618 7240.7328) (9910.916 7244.4427) (9908.3969 7245.8015) (9905.8779 7244.4427) (9903.8321 7240.7328)
      (9902.5191 7235.6947) (9901.8168 7230.6412) (9901.3588 7226.855) (9900.5038 7225.1756) (9898.7023 7225.771)
      (9895.6947 7228.1069) (9891.6336 7231.1908) (9887.1298 7233.8168) (9883.0687 7234.9924) (9880.3359 7234.1679)
      (9879.5115 7231.4351) (9880.687 7227.374) (9883.313 7222.8702) (9886.3969 7218.8092) (9888.7328 7215.8015)
      (9889.3282 7214.0) (9887.6489 7213.145) (9883.8626 7212.687) (9878.8092 7211.9847) (9873.771 7210.6718)
      (9870.0611 7208.626)
    ))
    ; P3290 -- see feature_dimensions_mm.csv
    ("06_ORNAMENT" 1 (
      (9876.3359 5007.6336) (9876.7481 5005.0534) (9877.9389 5002.626) (9879.8321 5000.4275) (9882.2901 4998.5954)
      (9885.1298 4997.145) (9888.1527 4996.0916) (9891.1908 4995.374) (9894.0305 4994.9313) (9896.5496 4994.6107)
      (9898.6412 4994.2901) (9900.2748 4993.8168) (9901.4351 4993.0382) (9902.2137 4991.8779) (9902.687 4990.2443)
      (9903.0076 4988.1527) (9903.3282 4985.6336) (9903.771 4982.7939) (9904.4885 4979.7557) (9905.542 4976.7328)
      (9906.9924 4973.8931) (9908.8244 4971.4351) (9911.0229 4969.542) (9913.4504 4968.3511) (9916.0305 4967.9389)
      (9918.6107 4968.3511) (9921.0382 4969.542) (9923.2366 4971.4351) (9925.0687 4973.8931) (9926.5191 4976.7328)
      (9927.5725 4979.7557) (9928.2901 4982.7939) (9928.7328 4985.6336) (9929.0534 4988.1527) (9929.374 4990.2443)
      (9929.8473 4991.8779) (9930.626 4993.0382) (9931.7863 4993.8168) (9933.4198 4994.2901) (9935.5115 4994.6107)
      (9938.0305 4994.9313) (9940.8702 4995.374) (9943.9084 4996.0916) (9946.9313 4997.145) (9949.771 4998.5954)
      (9952.229 5000.4275) (9954.1221 5002.626) (9955.313 5005.0534) (9955.7252 5007.6336) (9955.313 5010.2137)
      (9954.1221 5012.6412) (9952.229 5014.8397) (9949.771 5016.6718) (9946.9313 5018.1221) (9943.9084 5019.1756)
      (9940.8702 5019.8931) (9938.0305 5020.3359) (9935.5115 5020.6565) (9933.4198 5020.9771) (9931.7863 5021.4504)
      (9930.626 5022.229) (9929.8473 5023.3893) (9929.374 5025.0229) (9929.0534 5027.1145) (9928.7328 5029.6336)
      (9928.2901 5032.4733) (9927.5725 5035.5115) (9926.5191 5038.5344) (9925.0687 5041.374) (9923.2366 5043.8321)
      (9921.0382 5045.7252) (9918.6107 5046.916) (9916.0305 5047.3282) (9913.4504 5046.916) (9911.0229 5045.7252)
      (9908.8244 5043.8321) (9906.9924 5041.374) (9905.542 5038.5344) (9904.4885 5035.5115) (9903.771 5032.4733)
      (9903.3282 5029.6336) (9903.0076 5027.1145) (9902.687 5025.0229) (9902.2137 5023.3893) (9901.4351 5022.229)
      (9900.2748 5021.4504) (9898.6412 5020.9771) (9896.5496 5020.6565) (9894.0305 5020.3359) (9891.1908 5019.8931)
      (9888.1527 5019.1756) (9885.1298 5018.1221) (9882.2901 5016.6718) (9879.8321 5014.8397) (9877.9389 5012.6412)
      (9876.7481 5010.2137)
    ))
    ; P3291 -- see feature_dimensions_mm.csv
    ("06_ORNAMENT" 1 (
      (9899.2672 7389.313) (9899.9695 7385.8168) (9901.9389 7382.855) (9904.9008 7380.8855) (9908.3969 7380.1832)
      (9911.8931 7380.8855) (9914.855 7382.855) (9916.8244 7385.8168) (9917.5267 7389.313) (9916.8244 7392.8092)
      (9914.855 7395.771) (9911.8931 7397.7405) (9908.3969 7398.4427) (9904.9008 7397.7405) (9901.9389 7395.771)
      (9899.9695 7392.8092)
    ))
    ; P3292 -- see feature_dimensions_mm.csv
    ("06_ORNAMENT" 1 (
      (9899.2672 7206.1069) (9899.9695 7202.6107) (9901.9389 7199.6489) (9904.9008 7197.6794) (9908.3969 7196.9771)
      (9911.8931 7197.6794) (9914.855 7199.6489) (9916.8244 7202.6107) (9917.5267 7206.1069) (9916.8244 7209.6031)
      (9914.855 7212.5649) (9911.8931 7214.5344) (9908.3969 7215.2366) (9904.9008 7214.5344) (9901.9389 7212.5649)
      (9899.9695 7209.6031)
    ))
    ; P3293 -- see feature_dimensions_mm.csv
    ("06_ORNAMENT" 1 (
      (9914.8702 5232.9313) (9915.8626 5226.7023) (9918.7176 5221.084) (9923.1756 5216.626) (9928.7939 5213.7557)
      (9935.0229 5212.7786) (9941.2519 5213.7557) (9946.8702 5216.626) (9951.3282 5221.084) (9954.1832 5226.7023)
      (9955.1756 5232.9313) (9954.1832 5239.1603) (9951.3282 5244.7786) (9946.8702 5249.2366) (9941.2519 5252.0916)
      (9935.0229 5253.084) (9928.7939 5252.0916) (9923.1756 5249.2366) (9918.7176 5244.7786) (9915.8626 5239.1603)
    ))
    ; P3294 -- see feature_dimensions_mm.csv
    ("06_ORNAMENT" 1 (
      (9914.8702 4767.0687) (9915.8626 4760.8397) (9918.7176 4755.2214) (9923.1756 4750.7634) (9928.7939 4747.9084)
      (9935.0229 4746.916) (9941.2519 4747.9084) (9946.8702 4750.7634) (9951.3282 4755.2214) (9954.1832 4760.8397)
      (9955.1756 4767.0687) (9954.1832 4773.2977) (9951.3282 4778.916) (9946.8702 4783.374) (9941.2519 4786.2443)
      (9935.0229 4787.2214) (9928.7939 4786.2443) (9923.1756 4783.374) (9918.7176 4778.916) (9915.8626 4773.2977)
    ))
    ; P3295 -- see feature_dimensions_mm.csv
    ("06_ORNAMENT" 1 (
      (9914.8702 4637.5115) (9915.8626 4631.2824) (9918.7176 4625.6641) (9923.1756 4621.2061) (9928.7939 4618.3359)
      (9935.0229 4617.3588) (9941.2519 4618.3359) (9946.8702 4621.2061) (9951.3282 4625.6641) (9954.1832 4631.2824)
      (9955.1756 4637.5115) (9954.1832 4643.7405) (9951.3282 4649.3588) (9946.8702 4653.8168) (9941.2519 4656.6718)
      (9935.0229 4657.6641) (9928.7939 4656.6718) (9923.1756 4653.8168) (9918.7176 4649.3588) (9915.8626 4643.7405)
    ))
    ; P3296 -- see feature_dimensions_mm.csv
    ("06_ORNAMENT" 1 (
      (9914.8702 4171.6489) (9915.8626 4165.4198) (9918.7176 4159.8015) (9923.1756 4155.3435) (9928.7939 4152.4885)
      (9935.0229 4151.4962) (9941.2519 4152.4885) (9946.8702 4155.3435) (9951.3282 4159.8015) (9954.1832 4165.4198)
      (9955.1756 4171.6489) (9954.1832 4177.8779) (9951.3282 4183.4962) (9946.8702 4187.9542) (9941.2519 4190.8244)
      (9935.0229 4191.8015) (9928.7939 4190.8244) (9923.1756 4187.9542) (9918.7176 4183.4962) (9915.8626 4177.8779)
    ))
    ; P3297 -- see feature_dimensions_mm.csv
    ("06_ORNAMENT" 1 (
      (9914.8702 4042.0916) (9915.8626 4035.8626) (9918.7176 4030.2443) (9923.1756 4025.7863) (9928.7939 4022.916)
      (9935.0229 4021.9389) (9941.2519 4022.916) (9946.8702 4025.7863) (9951.3282 4030.2443) (9954.1832 4035.8626)
      (9955.1756 4042.0916) (9954.1832 4048.3206) (9951.3282 4053.9389) (9946.8702 4058.3969) (9941.2519 4061.2519)
      (9935.0229 4062.2443) (9928.7939 4061.2519) (9923.1756 4058.3969) (9918.7176 4053.9389) (9915.8626 4048.3206)
    ))
    ; P3298 -- see feature_dimensions_mm.csv
    ("06_ORNAMENT" 1 (
      (9919.1908 5148.0763) (9920.3969 5143.542) (9923.7252 5140.229) (9928.2595 5139.0076) (9932.7939 5140.229)
      (9936.1069 5143.542) (9937.3282 5148.0763) (9936.1069 5152.6107) (9932.7939 5155.9389) (9928.2595 5157.145)
      (9923.7252 5155.9389) (9920.3969 5152.6107)
    ))
    ; P3299 -- see feature_dimensions_mm.csv
    ("06_ORNAMENT" 1 (
      (9919.1908 4851.9084) (9920.3969 4847.374) (9923.7252 4844.0611) (9928.2595 4842.8397) (9932.7939 4844.0611)
      (9936.1069 4847.374) (9937.3282 4851.9084) (9936.1069 4856.4427) (9932.7939 4859.771) (9928.2595 4860.9771)
      (9923.7252 4859.771) (9920.3969 4856.4427)
    ))
    ; P3300 -- see feature_dimensions_mm.csv
    ("06_ORNAMENT" 1 (
      (9919.1908 4552.6565) (9920.3969 4548.1221) (9923.7252 4544.8092) (9928.2595 4543.5878) (9932.7939 4544.8092)
      (9936.1069 4548.1221) (9937.3282 4552.6565) (9936.1069 4557.1908) (9932.7939 4560.5191) (9928.2595 4561.7252)
      (9923.7252 4560.5191) (9920.3969 4557.1908)
    ))
    ; P3301 -- see feature_dimensions_mm.csv
    ("06_ORNAMENT" 1 (
      (9919.1908 4256.4885) (9920.3969 4251.9542) (9923.7252 4248.6412) (9928.2595 4247.4198) (9932.7939 4248.6412)
      (9936.1069 4251.9542) (9937.3282 4256.4885) (9936.1069 4261.0229) (9932.7939 4264.3511) (9928.2595 4265.5573)
      (9923.7252 4264.3511) (9920.3969 4261.0229)
    ))
    ; P3302 -- see feature_dimensions_mm.csv
    ("06_ORNAMENT" 1 (
      (9919.1908 3957.2366) (9920.3969 3952.7176) (9923.7252 3949.3893) (9928.2595 3948.1679) (9932.7939 3949.3893)
      (9936.1069 3952.7176) (9937.3282 3957.2366) (9936.1069 3961.771) (9932.7939 3965.0992) (9928.2595 3966.3053)
      (9923.7252 3965.0992) (9920.3969 3961.771)
    ))
    ; P3303 -- see feature_dimensions_mm.csv
    ("06_ORNAMENT" 1 (
      (9965.0534 4783.2672) (9966.2748 4778.7328) (9969.5878 4775.4198) (9974.1221 4774.1985) (9978.6565 4775.4198)
      (9981.9695 4778.7328) (9983.1908 4783.2672) (9981.9695 4787.8015) (9978.6565 4791.1145) (9974.1221 4792.3359)
      (9969.5878 4791.1145) (9966.2748 4787.8015)
    ))
    ; P3304 -- see feature_dimensions_mm.csv
    ("06_ORNAMENT" 1 (
      (9965.0534 4621.313) (9966.2748 4616.7786) (9969.5878 4613.4656) (9974.1221 4612.2443) (9978.6565 4613.4656)
      (9981.9695 4616.7786) (9983.1908 4621.313) (9981.9695 4625.8473) (9978.6565 4629.1603) (9974.1221 4630.3817)
      (9969.5878 4629.1603) (9966.2748 4625.8473)
    ))
    ; P3305 -- see feature_dimensions_mm.csv
    ("06_ORNAMENT" 1 (
      (9965.0534 4187.8473) (9966.2748 4183.313) (9969.5878 4180.0) (9974.1221 4178.7786) (9978.6565 4180.0)
      (9981.9695 4183.313) (9983.1908 4187.8473) (9981.9695 4192.3817) (9978.6565 4195.6947) (9974.1221 4196.916)
      (9969.5878 4195.6947) (9966.2748 4192.3817)
    ))
    ; P3306 -- see feature_dimensions_mm.csv
    ("06_ORNAMENT" 1 (
      (9965.0534 4025.8931) (9966.2748 4021.3588) (9969.5878 4018.0458) (9974.1221 4016.8244) (9978.6565 4018.0458)
      (9981.9695 4021.3588) (9983.1908 4025.8931) (9981.9695 4030.4275) (9978.6565 4033.7405) (9974.1221 4034.9618)
      (9969.5878 4033.7405) (9966.2748 4030.4275)
    ))
    ; P3307 -- see feature_dimensions_mm.csv
    ("06_ORNAMENT" 1 (
      (9977.8626 5138.2137) (9979.084 5132.0916) (9982.5649 5126.8855) (9987.7557 5123.4046) (9993.8931 5122.1832)
      (10000.0305 5123.4046) (10005.2214 5126.8855) (10008.7023 5132.0916) (10009.9237 5138.2137) (10008.7023 5144.3511)
      (10005.2214 5149.5573) (10000.0305 5153.0229) (9993.8931 5154.2443) (9987.7557 5153.0229) (9982.5649 5149.5573)
      (9979.084 5144.3511)
    ))
    ; P3308 -- see feature_dimensions_mm.csv
    ("06_ORNAMENT" 1 (
      (9977.8626 5061.8779) (9979.084 5055.7557) (9982.5649 5050.5496) (9987.7557 5047.0687) (9993.8931 5045.8473)
      (10000.0305 5047.0687) (10005.2214 5050.5496) (10008.7023 5055.7557) (10009.9237 5061.8779) (10008.7023 5068.0153)
      (10005.2214 5073.2214) (10000.0305 5076.687) (9993.8931 5077.9084) (9987.7557 5076.687) (9982.5649 5073.2214)
      (9979.084 5068.0153)
    ))
    ; P3309 -- see feature_dimensions_mm.csv
    ("06_ORNAMENT" 1 (
      (9977.8626 4985.542) (9979.084 4979.4198) (9982.5649 4974.2137) (9987.7557 4970.7328) (9993.8931 4969.5115)
      (10000.0305 4970.7328) (10005.2214 4974.2137) (10008.7023 4979.4198) (10009.9237 4985.542) (10008.7023 4991.6794)
      (10005.2214 4996.8855) (10000.0305 5000.3511) (9993.8931 5001.5725) (9987.7557 5000.3511) (9982.5649 4996.8855)
      (9979.084 4991.6794)
    ))
    ; P3310 -- see feature_dimensions_mm.csv
    ("06_ORNAMENT" 1 (
      (9977.8626 4909.2061) (9979.084 4903.084) (9982.5649 4897.8779) (9987.7557 4894.3969) (9993.8931 4893.1756)
      (10000.0305 4894.3969) (10005.2214 4897.8779) (10008.7023 4903.084) (10009.9237 4909.2061) (10008.7023 4915.3435)
      (10005.2214 4920.5496) (10000.0305 4924.0153) (9993.8931 4925.2366) (9987.7557 4924.0153) (9982.5649 4920.5496)
      (9979.084 4915.3435)
    ))
    ; P3311 -- see feature_dimensions_mm.csv
    ("06_ORNAMENT" 1 (
      (9977.8626 4832.8702) (9979.084 4826.7481) (9982.5649 4821.542) (9987.7557 4818.0611) (9993.8931 4816.8397)
      (10000.0305 4818.0611) (10005.2214 4821.542) (10008.7023 4826.7481) (10009.9237 4832.8702) (10008.7023 4839.0076)
      (10005.2214 4844.2137) (10000.0305 4847.6794) (9993.8931 4848.9008) (9987.7557 4847.6794) (9982.5649 4844.2137)
      (9979.084 4839.0076)
    ))
    ; P3312 -- see feature_dimensions_mm.csv
    ("06_ORNAMENT" 1 (
      (9977.8626 4527.5267) (9979.084 4521.4046) (9982.5649 4516.1985) (9987.7557 4512.7176) (9993.8931 4511.4962)
      (10000.0305 4512.7176) (10005.2214 4516.1985) (10008.7023 4521.4046) (10009.9237 4527.5267) (10008.7023 4533.6641)
      (10005.2214 4538.8702) (10000.0305 4542.3359) (9993.8931 4543.5573) (9987.7557 4542.3359) (9982.5649 4538.8702)
      (9979.084 4533.6641)
    ))
    ; P3313 -- see feature_dimensions_mm.csv
    ("06_ORNAMENT" 1 (
      (9977.8626 4374.855) (9979.084 4368.7328) (9982.5649 4363.5267) (9987.7557 4360.0458) (9993.8931 4358.8244)
      (10000.0305 4360.0458) (10005.2214 4363.5267) (10008.7023 4368.7328) (10009.9237 4374.855) (10008.7023 4380.9924)
      (10005.2214 4386.1985) (10000.0305 4389.6641) (9993.8931 4390.8855) (9987.7557 4389.6641) (9982.5649 4386.1985)
      (9979.084 4380.9924)
    ))
    ; P3314 -- see feature_dimensions_mm.csv
    ("06_ORNAMENT" 1 (
      (9977.8626 4298.5191) (9979.084 4292.3969) (9982.5649 4287.1908) (9987.7557 4283.7099) (9993.8931 4282.4885)
      (10000.0305 4283.7099) (10005.2214 4287.1908) (10008.7023 4292.3969) (10009.9237 4298.5191) (10008.7023 4304.6565)
      (10005.2214 4309.8626) (10000.0305 4313.3282) (9993.8931 4314.5496) (9987.7557 4313.3282) (9982.5649 4309.8626)
      (9979.084 4304.6565)
    ))
    ; P3315 -- see feature_dimensions_mm.csv
    ("06_ORNAMENT" 1 (
      (9977.8626 4222.1832) (9979.084 4216.0611) (9982.5649 4210.855) (9987.7557 4207.374) (9993.8931 4206.1527)
      (10000.0305 4207.374) (10005.2214 4210.855) (10008.7023 4216.0611) (10009.9237 4222.1832) (10008.7023 4228.3206)
      (10005.2214 4233.5267) (10000.0305 4236.9924) (9993.8931 4238.2137) (9987.7557 4236.9924) (9982.5649 4233.5267)
      (9979.084 4228.3206)
    ))
    ; P3316 -- see feature_dimensions_mm.csv
    ("06_ORNAMENT" 1 (
      (9977.8626 3916.8397) (9979.084 3910.7176) (9982.5649 3905.5115) (9987.7557 3902.0305) (9993.8931 3900.8092)
      (10000.0305 3902.0305) (10005.2214 3905.5115) (10008.7023 3910.7176) (10009.9237 3916.8397) (10008.7023 3922.9771)
      (10005.2214 3928.1832) (10000.0305 3931.6489) (9993.8931 3932.8702) (9987.7557 3931.6489) (9982.5649 3928.1832)
      (9979.084 3922.9771)
    ))
    ; P3317 -- see feature_dimensions_mm.csv
    ("06_ORNAMENT" 1 (
      (9981.1603 4106.8702) (9982.3817 4102.3359) (9985.6947 4099.0229) (9990.229 4097.8015) (9994.7634 4099.0229)
      (9998.0763 4102.3359) (9999.2977 4106.8702) (9998.0763 4111.4046) (9994.7634 4114.7176) (9990.229 4115.9389)
      (9985.6947 4114.7176) (9982.3817 4111.4046)
    ))
    ; P3318 -- see feature_dimensions_mm.csv
    ("06_ORNAMENT" 1 (
      (10570.9924 7374.0458) (10572.3511 7371.5267) (10576.0611 7369.4809) (10581.0992 7368.1527) (10586.1527 7367.4656)
      (10589.9389 7367.0076) (10591.6183 7366.1527) (10591.0229 7364.3511) (10588.687 7361.3435) (10585.6031 7357.2824)
      (10582.9771 7352.7786) (10581.8015 7348.7176) (10582.626 7345.9847) (10585.3588 7345.1603) (10589.4198 7346.3359)
      (10593.9237 7348.9618) (10597.9847 7352.0458) (10600.9924 7354.3817) (10602.7939 7354.9771) (10603.6489 7353.2977)
      (10604.1069 7349.5115) (10604.8092 7344.458) (10606.1221 7339.4198) (10608.1679 7335.7099) (10610.687 7334.3511)
      (10613.2061 7335.7099) (10615.2519 7339.4198) (10616.5802 7344.458) (10617.2672 7349.5115) (10617.7252 7353.2977)
      (10618.5802 7354.9771) (10620.3817 7354.3817) (10623.3893 7352.0458) (10627.4504 7348.9618) (10631.9542 7346.3359)
      (10636.0153 7345.1603) (10638.7481 7345.9847) (10639.5725 7348.7176) (10638.3969 7352.7786) (10635.771 7357.2824)
      (10632.687 7361.3435) (10630.3511 7364.3511) (10629.7557 7366.1527) (10631.4351 7367.0076) (10635.2214 7367.4656)
      (10640.2748 7368.1527) (10645.313 7369.4809) (10649.0229 7371.5267) (10650.3817 7374.0458) (10649.0229 7376.5649)
      (10645.313 7378.6107) (10640.2748 7379.9237) (10635.2214 7380.626) (10631.4351 7381.084) (10629.7557 7381.9389)
      (10630.3511 7383.7405) (10632.687 7386.7481) (10635.771 7390.8092) (10638.3969 7395.313) (10639.5725 7399.374)
      (10638.7481 7402.1069) (10636.0153 7402.9313) (10631.9542 7401.7557) (10627.4504 7399.1298) (10623.3893 7396.0458)
      (10620.3817 7393.7099) (10618.5802 7393.1145) (10617.7252 7394.7939) (10617.2672 7398.5802) (10616.5802 7403.6336)
      (10615.2519 7408.6718) (10613.2061 7412.3817) (10610.687 7413.7405) (10608.1679 7412.3817) (10606.1221 7408.6718)
      (10604.8092 7403.6336) (10604.1069 7398.5802) (10603.6489 7394.7939) (10602.7939 7393.1145) (10600.9924 7393.7099)
      (10597.9847 7396.0458) (10593.9237 7399.1298) (10589.4198 7401.7557) (10585.3588 7402.9313) (10582.626 7402.1069)
      (10581.8015 7399.374) (10582.9771 7395.313) (10585.6031 7390.8092) (10588.687 7386.7481) (10591.0229 7383.7405)
      (10591.6183 7381.9389) (10589.9389 7381.084) (10586.1527 7380.626) (10581.0992 7379.9237) (10576.0611 7378.6107)
      (10572.3511 7376.5649)
    ))
    ; P3319 -- see feature_dimensions_mm.csv
    ("06_ORNAMENT" 1 (
      (10570.9924 7206.1069) (10572.3511 7203.5878) (10576.0611 7201.542) (10581.0992 7200.2137) (10586.1527 7199.5267)
      (10589.9389 7199.0687) (10591.6183 7198.2137) (10591.0229 7196.4122) (10588.687 7193.4046) (10585.6031 7189.3435)
      (10582.9771 7184.8397) (10581.8015 7180.7786) (10582.626 7178.0458) (10585.3588 7177.2214) (10589.4198 7178.3969)
      (10593.9237 7181.0229) (10597.9847 7184.1069) (10600.9924 7186.4427) (10602.7939 7187.0382) (10603.6489 7185.3588)
      (10604.1069 7181.5725) (10604.8092 7176.5191) (10606.1221 7171.4809) (10608.1679 7167.771) (10610.687 7166.4122)
      (10613.2061 7167.771) (10615.2519 7171.4809) (10616.5802 7176.5191) (10617.2672 7181.5725) (10617.7252 7185.3588)
      (10618.5802 7187.0382) (10620.3817 7186.4427) (10623.3893 7184.1069) (10627.4504 7181.0229) (10631.9542 7178.3969)
      (10636.0153 7177.2214) (10638.7481 7178.0458) (10639.5725 7180.7786) (10638.3969 7184.8397) (10635.771 7189.3435)
      (10632.687 7193.4046) (10630.3511 7196.4122) (10629.7557 7198.2137) (10631.4351 7199.0687) (10635.2214 7199.5267)
      (10640.2748 7200.2137) (10645.313 7201.542) (10649.0229 7203.5878) (10650.3817 7206.1069) (10649.0229 7208.626)
      (10645.313 7210.6718) (10640.2748 7211.9847) (10635.2214 7212.687) (10631.4351 7213.145) (10629.7557 7214.0)
      (10630.3511 7215.8015) (10632.687 7218.8092) (10635.771 7222.8702) (10638.3969 7227.374) (10639.5725 7231.4351)
      (10638.7481 7234.1679) (10636.0153 7234.9924) (10631.9542 7233.8168) (10627.4504 7231.1908) (10623.3893 7228.1069)
      (10620.3817 7225.771) (10618.5802 7225.1756) (10617.7252 7226.855) (10617.2672 7230.6412) (10616.5802 7235.6947)
      (10615.2519 7240.7328) (10613.2061 7244.4427) (10610.687 7245.8015) (10608.1679 7244.4427) (10606.1221 7240.7328)
      (10604.8092 7235.6947) (10604.1069 7230.6412) (10603.6489 7226.855) (10602.7939 7225.1756) (10600.9924 7225.771)
      (10597.9847 7228.1069) (10593.9237 7231.1908) (10589.4198 7233.8168) (10585.3588 7234.9924) (10582.626 7234.1679)
      (10581.8015 7231.4351) (10582.9771 7227.374) (10585.6031 7222.8702) (10588.687 7218.8092) (10591.0229 7215.8015)
      (10591.6183 7214.0) (10589.9389 7213.145) (10586.1527 7212.687) (10581.0992 7211.9847) (10576.0611 7210.6718)
      (10572.3511 7208.626)
    ))
    ; P3320 -- see feature_dimensions_mm.csv
    ("06_ORNAMENT" 1 (
      (10601.5573 7374.0458) (10602.2595 7370.5496) (10604.229 7367.5878) (10607.1908 7365.6183) (10610.687 7364.916)
      (10614.1832 7365.6183) (10617.145 7367.5878) (10619.1145 7370.5496) (10619.8168 7374.0458) (10619.1145 7377.542)
      (10617.145 7380.5038) (10614.1832 7382.4733) (10610.687 7383.1756) (10607.1908 7382.4733) (10604.229 7380.5038)
      (10602.2595 7377.542)
    ))
    ; P3321 -- see feature_dimensions_mm.csv
    ("06_ORNAMENT" 1 (
      (10601.5573 7206.1069) (10602.2595 7202.6107) (10604.229 7199.6489) (10607.1908 7197.6794) (10610.687 7196.9771)
      (10614.1832 7197.6794) (10617.145 7199.6489) (10619.1145 7202.6107) (10619.8168 7206.1069) (10619.1145 7209.6031)
      (10617.145 7212.5649) (10614.1832 7214.5344) (10610.687 7215.2366) (10607.1908 7214.5344) (10604.229 7212.5649)
      (10602.2595 7209.6031)
    ))
    ; P3322 -- see feature_dimensions_mm.csv
    ("06_ORNAMENT" 1 (
      (10694.458 5185.8779) (10696.3359 5185.7252) (10703.0534 5186.5649) (10709.1145 5189.4504) (10715.1298 5194.458)
      (10720.8702 5201.0534) (10726.0916 5208.687) (10730.5954 5216.8244) (10734.1374 5224.916) (10736.4733 5232.4122)
      (10737.4046 5238.7786) (10736.0 5244.4275) (10732.0763 5250.0458) (10726.5191 5255.5115) (10720.229 5260.7176)
      (10714.0763 5265.5267) (10708.9618 5269.8473) (10705.7557 5273.542) (10705.3435 5276.4885) (10708.0153 5278.9771)
      (10713.0382 5281.2214) (10719.8015 5283.0534) (10727.6794 5284.2901) (10736.0458 5284.7176) (10744.3053 5284.1679)
      (10751.8321 5282.458) (10758.0153 5279.3893) (10763.374 5274.7176) (10768.7176 5268.5344) (10773.8626 5261.1145)
      (10778.626 5252.7328) (10782.8244 5243.7099) (10786.2443 5234.3206) (10788.7328 5224.8397) (10790.0763 5215.5725)
      (10790.5191 5206.0611) (10790.3511 5195.8168) (10789.4198 5185.1145) (10787.6489 5174.229) (10784.8702 5163.4504)
      (10781.0076 5153.0229) (10775.9084 5143.2366) (10769.4656 5134.3511) (10760.3969 5126.8092) (10740.3664 5145.5878)
      (10700.0611 5181.2061)
    ))
    ; P3323 -- see feature_dimensions_mm.csv
    ("06_ORNAMENT" 1 (
      (10699.4504 4207.2672) (10703.8626 4206.6565) (10728.0763 4204.7023) (10755.5878 4203.9237) (10763.4351 4204.1985)
      (10756.4885 4196.0) (10749.6947 4186.0458) (10748.4427 4183.4809) (10737.9389 4186.8855) (10725.4198 4188.9466)
      (10712.9771 4189.5725) (10712.0 4190.9008)
    ))
    ; P3324 -- see feature_dimensions_mm.csv
    ("06_ORNAMENT" 1 (
      (10702.2901 5816.7939) (10716.2137 5798.0305) (10732.5954 5778.5649) (10751.1603 5758.7176) (10756.9924 5753.0382)
      (10758.5802 5748.2595) (10762.4122 5739.0382) (10766.4122 5731.2977) (10771.084 5724.6718) (10776.8397 5718.626)
      (10783.374 5713.3435) (10790.3511 5708.9618) (10797.4046 5705.6641) (10804.2443 5703.6031) (10810.5038 5702.9313)
      (10813.084 5703.3588) (10817.3282 5699.8931) (10841.9542 5681.5725) (10867.4351 5664.4122) (10874.855 5659.9389)
      (10874.1679 5658.1985) (10869.0076 5648.855) (10860.9771 5640.0611) (10849.374 5631.3893) (10835.8015 5623.0534)
      (10821.8321 5615.2672) (10809.0687 5608.2443) (10799.0992 5602.1985) (10793.5115 5597.3435) (10793.8931 5593.8931)
      (10801.8321 5591.084) (10816.5191 5588.3511) (10835.8931 5586.3053) (10857.9084 5585.4962) (10880.4885 5586.5038)
      (10901.6336 5589.8779) (10919.2519 5596.229) (10931.2977 5606.1069) (10938.1985 5620.8092) (10939.2366 5626.0763)
      (10946.229 5622.9466) (10972.3817 5613.5115) (10998.0305 5606.7786) (11022.9008 5603.0534) (11008.5802 5625.4656)
      (10991.2977 5647.3435) (10971.4656 5668.5649) (10949.4809 5688.9771) (10942.3664 5694.8092) (10940.8244 5714.4733)
      (10937.8626 5739.7863) (10934.5191 5763.1603) (10931.2977 5783.2061) (10927.8015 5800.9466) (10923.3435 5818.1221)
      (10918.0458 5834.4427) (10912.0611 5849.6183) (10905.4962 5863.3588) (10898.4885 5875.374) (10891.1756 5885.4046)
      (10883.6641 5893.1298) (10875.6336 5898.3817) (10866.8092 5901.3282) (10857.4198 5902.2901) (10847.7099 5901.5267)
      (10837.9237 5899.3282) (10828.2748 5895.9847) (10819.0229 5891.7863) (10810.3817 5887.0229) (10801.8473 5881.145)
      (10792.9771 5873.6336) (10784.1069 5864.8702) (10775.5725 5855.145) (10767.7252 5844.8397) (10760.916 5834.2748)
      (10755.4809 5823.8015) (10751.7557 5813.7405) (10749.9847 5804.2901) (10745.8626 5805.771) (10723.0992 5812.4122)
    ))
    ; P3325 -- see feature_dimensions_mm.csv
    ("06_ORNAMENT" 1 (
      (10817.7099 5798.4733) (10819.8473 5801.084) (10823.8626 5803.4656) (10829.2672 5805.3893) (10835.5725 5806.6718)
      (10842.2748 5807.1298) (10848.8855 5806.5649) (10854.9008 5804.7634) (10859.8473 5801.5267) (10864.1374 5796.6107)
      (10868.4122 5790.1069) (10872.5191 5782.2901) (10876.3359 5773.4656) (10879.6947 5763.9695) (10882.4275 5754.0763)
      (10884.4122 5744.1069) (10885.2061 5737.0382) (10874.8244 5743.8931) (10848.3817 5759.6031) (10842.6107 5762.7023)
      (10842.229 5764.7176) (10839.0992 5770.6412) (10834.6565 5776.3969) (10829.6183 5781.8626) (10824.7023 5786.9466)
      (10820.5954 5791.4809) (10818.0305 5795.374)
    ))
    ; P3326 -- see feature_dimensions_mm.csv
    ("06_ORNAMENT" 1 (
      (10826.8244 4072.8397) (10831.2519 4074.9466) (10837.2672 4079.9542) (10843.0076 4086.5496) (10848.229 4094.1832)
      (10852.7328 4102.3206) (10856.2748 4110.4122) (10858.6107 4117.9084) (10859.542 4124.2748) (10858.1374 4129.9237)
      (10854.2137 4135.542) (10848.6565 4141.0076) (10842.3664 4146.2137) (10836.2137 4151.0229) (10831.0992 4155.3435)
      (10827.8931 4159.0382) (10827.4809 4161.9847) (10830.1527 4164.4733) (10835.1756 4166.7176) (10841.9389 4168.5496)
      (10849.8168 4169.7863) (10858.1832 4170.2137) (10866.4427 4169.6641) (10873.9695 4167.9542) (10880.1527 4164.8855)
      (10885.5115 4160.2137) (10890.855 4154.0305) (10896.0 4146.6107) (10900.7634 4138.229) (10904.9618 4129.2061)
      (10908.3817 4119.8168) (10910.8702 4110.3359) (10912.2137 4101.0687) (10912.6565 4091.5573) (10912.4885 4081.313)
      (10911.5573 4070.6107) (10909.7863 4059.7252) (10907.0076 4048.9466) (10903.145 4038.5191) (10898.0458 4028.7328)
      (10891.6031 4019.8473) (10881.5573 4011.4962) (10867.0534 4003.2519) (10850.0916 3995.3435) (10843.0534 3992.3511)
      (10835.4198 4006.3817) (10832.6412 4011.0534) (10834.0153 4022.3969) (10833.1756 4040.0) (10830.2901 4058.1374)
    ))
    ; P3327 -- see feature_dimensions_mm.csv
    ("06_ORNAMENT" 1 (
      (10834.8244 3961.6641) (10846.6412 3960.7176) (10857.374 3950.7939) (10853.7405 3949.313) (10844.5649 3944.6412)
      (10841.3435 3950.6565)
    ))
    ; P3328 -- see feature_dimensions_mm.csv
    ("06_ORNAMENT" 1 (
      (10859.9084 3960.1527) (10877.7252 3959.6489) (10888.8244 3960.0305) (10883.5725 3959.1603) (10873.1298 3956.4885)
      (10863.2977 3953.1908)
    ))
    ; P3329 -- see feature_dimensions_mm.csv
    ("06_ORNAMENT" 1 (
      (10900.7634 1778.626) (10900.7634 1702.2901) (10912.5649 1704.1527) (10923.1908 1709.5725) (10931.6489 1718.0305)
      (10937.0687 1728.6565) (10938.9313 1740.458) (10937.0687 1752.2595) (10931.6489 1762.8855) (10923.1908 1771.3435)
      (10912.5649 1776.7634)
    ))
    ; P3330 -- see feature_dimensions_mm.csv
    ("06_ORNAMENT" 1 (
      (10900.7634 1592.2901) (10900.7634 1536.626) (10903.6031 1533.542) (10911.313 1528.1069) (10920.4885 1523.9389)
      (10930.9008 1521.1603) (10942.3053 1519.8168) (10954.4122 1519.9542) (10966.916 1521.5725) (10979.5267 1524.6107)
      (10991.9237 1529.0076) (11003.8015 1534.6565) (11014.8702 1541.4198) (11024.855 1549.1298) (11033.5115 1557.6031)
      (11040.626 1566.6107) (11046.0153 1575.9389) (11049.5573 1585.374) (11051.1756 1594.6565) (11050.8092 1603.5878)
      (11048.4733 1611.9237) (11044.229 1619.4656) (11038.1679 1626.0458) (11030.458 1631.4809) (11021.2824 1635.6336)
      (11010.8702 1638.4122) (10999.4809 1639.7557) (10987.374 1639.6183) (10974.855 1638.0153) (10962.2595 1634.9618)
      (10949.8626 1630.5649) (10937.9847 1624.916) (10926.916 1618.1527) (10916.9313 1610.4427) (10908.2748 1601.9847)
      (10901.1603 1592.9771)
    ))
    ; P3331 -- see feature_dimensions_mm.csv
    ("06_ORNAMENT" 1 (
      (10903.1145 1885.4809) (10908.2748 1878.9313) (10916.9313 1870.4733) (10926.916 1862.7634) (10937.9847 1856.0)
      (10949.8626 1850.3511) (10962.2595 1845.9542) (10974.855 1842.9008) (10987.374 1841.2977) (10999.4809 1841.1603)
      (11010.8702 1842.5038) (11021.2824 1845.2824) (11030.458 1849.4351) (11038.1679 1854.8702) (11044.229 1861.4504)
      (11048.4733 1868.9924) (11050.8092 1877.3282) (11051.1756 1886.2595) (11049.5573 1895.542) (11046.0153 1904.9771)
      (11040.626 1914.3053) (11033.5115 1923.313) (11024.855 1931.7863) (11014.8702 1939.4962) (11003.8015 1946.2595)
      (10991.9237 1951.9084) (10979.5267 1956.3053) (10966.916 1959.3435) (10954.4122 1960.9618) (10942.3053 1961.0992)
      (10930.9008 1959.7557) (10920.4885 1956.9771) (10916.1985 1955.0229) (10909.5573 1928.2748) (10904.687 1900.4733)
    ))
    ; P3332 -- see feature_dimensions_mm.csv
    ("06_ORNAMENT" 1 (
      (10961.8321 5954.1985) (10980.9466 5938.9313) (11002.7328 5923.5267) (11026.8397 5908.2443) (11052.916 5893.313)
      (11080.5954 5878.9618) (11109.542 5865.4656) (11139.374 5853.0382) (11169.7557 5841.9542) (11200.3206 5832.4122)
      (11230.7176 5824.7023) (11260.5954 5819.0382) (11289.5878 5815.6641) (11317.3435 5814.8397) (11343.5115 5816.7939)
      (11323.0229 5835.542) (11299.6641 5853.1145) (11273.9237 5869.4504) (11246.2137 5884.5191) (11217.0229 5898.2595)
      (11186.7786 5910.6107) (11155.9542 5921.5573) (11124.9924 5931.0229) (11094.3511 5938.9618) (11064.4885 5945.3435)
      (11035.8473 5950.1069) (11008.8855 5953.2061) (10984.0611 5954.5802)
    ))
    ; P3333 -- see feature_dimensions_mm.csv
    ("06_ORNAMENT" 1 (
      (10961.8321 1740.458) (10963.5267 1728.5191) (10968.5496 1716.8702) (10976.8092 1705.8015) (10988.0763 1695.5878)
      (11002.0763 1686.4733) (11018.4733 1678.7023) (11036.855 1672.4427) (11056.7786 1667.8626) (11077.7405 1665.0687)
      (11099.2366 1664.1221) (11120.7328 1665.0687) (11141.6947 1667.8626) (11161.6183 1672.4427) (11180.0 1678.7023)
      (11196.3969 1686.4733) (11210.3969 1695.5878) (11221.6641 1705.8015) (11229.9237 1716.8702) (11234.9466 1728.5191)
      (11236.6412 1740.458) (11234.9466 1752.3969) (11229.9237 1764.0458) (11221.6641 1775.1145) (11210.3969 1785.3282)
      (11196.3969 1794.4427) (11180.0 1802.2137) (11161.6183 1808.4733) (11141.6947 1813.0534) (11120.7328 1815.8473)
      (11099.2366 1816.7939) (11077.7405 1815.8473) (11056.7786 1813.0534) (11036.855 1808.4733) (11018.4733 1802.2137)
      (11002.0763 1794.4427) (10988.0763 1785.3282) (10976.8092 1775.1145) (10968.5496 1764.0458) (10963.5267 1752.3969)
    ))
    ; P3334 -- see feature_dimensions_mm.csv
    ("06_ORNAMENT" 1 (
      (10986.6565 6056.5496) (10987.9389 6050.8397) (10990.7328 6045.1298) (10994.7328 6039.6031) (10999.6031 6034.4275)
      (11005.0229 6029.8168) (11010.687 6025.9542) (11017.2977 6022.6412) (11025.4656 6019.6183) (11034.7176 6016.9771)
      (11044.5954 6014.7939) (11054.5954 6013.145) (11064.2748 6012.1069) (11073.1603 6011.771) (11080.7634 6012.2137)
      (11087.6336 6013.7252) (11094.4427 6016.3664) (11100.9466 6019.8321) (11106.8855 6023.8473) (11111.9695 6028.1374)
      (11115.9847 6032.3969) (11118.6412 6036.3359) (11119.6947 6039.6947) (11118.0916 6042.6718) (11113.6489 6045.6183)
      (11107.3588 6048.5038) (11100.229 6051.2366) (11093.2519 6053.771) (11087.4504 6056.0458) (11083.8168 6057.9847)
      (11083.3588 6059.542) (11086.3817 6060.855) (11092.0763 6062.0305) (11099.7405 6062.9924) (11108.6718 6063.6489)
      (11118.1527 6063.8779) (11127.5267 6063.5878) (11136.0458 6062.687) (11143.0534 6061.0687) (11149.1145 6058.6107)
      (11155.1756 6055.3588) (11161.0076 6051.4504) (11166.4122 6047.0382) (11171.1603 6042.2901) (11175.0534 6037.3435)
      (11177.8626 6032.3511) (11179.3893 6027.4809) (11179.8931 6022.4733) (11179.6947 6017.084) (11178.6565 6011.4504)
      (11176.626 6005.7252) (11173.4962 6000.0458) (11169.1145 5994.5649) (11163.3282 5989.4046) (11156.0305 5984.7328)
      (11144.6412 5980.3359) (11128.2137 5976.0) (11108.9771 5971.8321) (11089.2061 5967.9389) (11071.1145 5964.4275)
      (11056.9924 5961.4046) (11049.084 5958.9771) (11049.6183 5957.2519) (11060.8702 5955.8473) (11081.6794 5954.4885)
      (11109.1145 5953.4656) (11140.2901 5953.0534) (11172.3053 5953.5573) (11202.2443 5955.2519) (11227.2061 5958.4275)
      (11244.2748 5963.3588) (11254.0458 5970.7176) (11259.542 5980.4885) (11261.4962 5992.0) (11260.6565 6004.5802)
      (11257.771 6017.542) (11253.5878 6030.1985) (11248.8397 6041.8779) (11244.2748 6051.9084) (11239.313 6060.7786)
      (11233.0076 6069.374) (11225.5115 6077.5267) (11218.0153 6084.229) (11237.1298 6073.2061) (11267.7252 6057.1298)
      (11300.1221 6041.6031) (11316.5649 6034.4427) (11316.7939 6033.5878) (11319.3435 6033.2214) (11333.8779 6026.8855)
      (11368.5954 6013.2519) (11403.8473 6000.9313) (11439.2061 5990.2137) (11474.2748 5981.3282) (11508.5954 5974.5496)
      (11541.7863 5970.1527) (11573.4198 5968.3664) (11603.0534 5969.4656) (11578.5649 5989.2366) (11550.9008 6007.8931)
      (11520.5802 6025.374) (11489.8321 6040.7939) (11497.1756 6047.0534) (11502.0153 6056.8244) (11503.7405 6068.3359)
      (11503.0076 6080.916) (11500.458 6093.8779) (11496.7634 6106.5344) (11492.5802 6118.2137) (11488.5496 6128.2443)
      (11484.1679 6137.1145) (11478.5954 6145.7099) (11471.9847 6153.8626) (11464.5038 6161.4504) (11456.3053 6168.3206)
      (11447.542 6174.3359) (11438.3969 6179.3435) (11429.0076 6183.2061) (11418.9618 6185.8321) (11407.9389 6187.313)
      (11396.1985 6187.7863) (11384.0611 6187.4046) (11371.8168 6186.3053) (11359.771 6184.6412) (11348.1985 6182.5344)
      (11337.4046 6180.1527) (11326.7481 6177.2061) (11315.6489 6173.4656) (11304.5496 6169.0687) (11293.8931 6164.2137)
      (11284.0916 6159.0687) (11275.5725 6153.7863) (11268.7786 6148.5344) (11264.1221 6143.5115) (11261.7252 6138.3969)
      (11261.2366 6132.8855) (11262.3664 6127.1756) (11264.8397 6121.4656) (11268.3664 6115.9389) (11272.6565 6110.7634)
      (11272.9618 6110.4733) (11244.7328 6115.4656) (11213.8779 6119.5267) (11185.5725 6121.771) (11160.3053 6122.1374)
      (11183.0076 6105.9695) (11188.3359 6102.5649) (11187.4351 6103.0076) (11176.7939 6106.8702) (11165.4198 6109.4962)
      (11152.9008 6110.9771) (11139.6183 6111.4504) (11125.8626 6111.0687) (11111.9847 6109.9695) (11098.3206 6108.3053)
      (11085.2061 6106.1985) (11072.9771 6103.8168) (11060.8855 6100.8702) (11048.3206 6097.1298) (11035.7557 6092.7328)
      (11023.6641 6087.8779) (11012.5496 6082.7328) (11002.9008 6077.4504) (10995.1908 6072.1985) (10989.9237 6067.1756)
      (10987.2214 6062.0611)
    ))
    ; P3335 -- see feature_dimensions_mm.csv
    ("06_ORNAMENT" 1 (
      (10996.7481 2064.3206) (10998.6107 2052.5344) (11004.0305 2041.8931) (11012.4733 2033.4504) (11023.1145 2028.0305)
      (11034.916 2026.1527) (11046.7023 2028.0305) (11057.3435 2033.4504) (11065.7863 2041.8931) (11071.2061 2052.5344)
      (11073.084 2064.3206) (11071.2061 2076.1221) (11065.7863 2086.7634) (11057.3435 2095.2061) (11046.7023 2100.626)
      (11034.916 2102.4885) (11023.1145 2100.626) (11012.4733 2095.2061) (11004.0305 2086.7634) (10998.6107 2076.1221)
    ))
    ; P3336 -- see feature_dimensions_mm.csv
    ("06_ORNAMENT" 1 (
      (10996.7481 1416.5954) (10998.6107 1404.7939) (11004.0305 1394.1527) (11012.4733 1385.7099) (11023.1145 1380.2901)
      (11034.916 1378.4275) (11040.8244 1379.3588) (11039.4046 1377.9695) (11038.1679 1374.0458) (11039.4046 1370.1221)
      (11042.9466 1366.6412) (11048.2137 1363.8931) (11054.4122 1362.0305) (11060.5954 1360.9313) (11065.9389 1360.2443)
      (11069.7557 1359.5115) (11071.7405 1358.1679) (11071.9084 1355.7863) (11070.6412 1352.1069) (11068.5649 1347.145)
      (11066.4122 1341.2214) (11064.9313 1334.9313) (11064.6718 1329.0076) (11065.9237 1324.1985) (11068.7023 1321.1603)
      (11072.7176 1320.2748) (11077.5115 1321.5878) (11082.5191 1324.7786) (11087.2214 1329.2214) (11091.2824 1334.0305)
      (11094.5344 1338.3053) (11097.084 1341.2519) (11099.2366 1342.2901) (11101.3893 1341.2519) (11103.9389 1338.3053)
      (11107.1908 1334.0305) (11111.2519 1329.2214) (11115.9542 1324.7786) (11120.9618 1321.5878) (11125.7557 1320.2748)
      (11129.771 1321.1603) (11132.5496 1324.1985) (11133.8015 1329.0076) (11133.542 1334.9313) (11132.0611 1341.2214)
      (11129.9084 1347.145) (11127.8321 1352.1069) (11126.5649 1355.7863) (11126.7328 1358.1679) (11128.7176 1359.5115)
      (11132.5344 1360.2443) (11137.8779 1360.9313) (11143.1603 1361.8779) (11142.9313 1361.2061) (11139.8931 1348.5954)
      (11138.2748 1336.0916) (11138.1374 1323.9847) (11139.4809 1312.5802) (11142.2595 1302.1679) (11146.4275 1292.9924)
      (11151.8626 1285.2824) (11158.4275 1279.2366) (11165.9695 1274.9924) (11174.3206 1272.6565) (11183.2366 1272.2901)
      (11192.5344 1273.8931) (11201.9542 1277.4504) (11211.2977 1282.8397) (11220.3053 1289.9542) (11228.7634 1298.6107)
      (11236.4733 1308.5954) (11243.2366 1319.6641) (11248.8855 1331.542) (11253.2824 1343.9389) (11256.3359 1356.5344)
      (11257.9389 1369.0534) (11258.0763 1381.145) (11256.7328 1392.5496) (11253.9542 1402.9618) (11249.8015 1412.1374)
      (11244.3664 1419.8473) (11237.7863 1425.9084) (11230.2443 1430.1527) (11221.9084 1432.4885) (11212.9771 1432.855)
      (11203.6947 1431.2366) (11194.2595 1427.6947) (11184.9313 1422.3053) (11175.9237 1415.1908) (11167.4504 1406.5344)
      (11159.7405 1396.5496) (11152.9771 1385.4809) (11151.9542 1383.313) (11150.2595 1384.1985) (11144.0611 1386.0611)
      (11137.8779 1387.1603) (11132.5344 1387.8473) (11128.7176 1388.5802) (11126.7328 1389.9237) (11126.5649 1392.3053)
      (11127.8321 1395.9847) (11129.9084 1400.9466) (11132.0611 1406.8702) (11133.542 1413.1603) (11133.8015 1419.084)
      (11132.5496 1423.8931) (11129.771 1426.9313) (11125.7557 1427.8168) (11120.9618 1426.5038) (11115.9542 1423.313)
      (11111.2519 1418.8702) (11107.1908 1414.0611) (11103.9389 1409.7863) (11101.3893 1406.8397) (11099.2366 1405.8015)
      (11097.084 1406.8397) (11094.5344 1409.7863) (11091.2824 1414.0611) (11087.2214 1418.8702) (11082.5191 1423.313)
      (11077.5115 1426.5038) (11072.7176 1427.8168) (11071.3435 1427.5115) (11071.2061 1428.3817) (11065.7863 1439.0229)
      (11057.3435 1447.4656) (11046.7023 1452.8855) (11034.916 1454.7634) (11023.1145 1452.8855) (11012.4733 1447.4656)
      (11004.0305 1439.0229) (10998.6107 1428.3817)
    ))
    ; P3337 -- see feature_dimensions_mm.csv
    ("06_ORNAMENT" 1 (
      (11038.1679 2137.4046) (11039.4046 2133.4809) (11042.9466 2130.0) (11048.2137 2127.2519) (11054.4122 2125.3893)
      (11060.5954 2124.2901) (11065.9389 2123.6031) (11069.7557 2122.8702) (11071.7405 2121.5267) (11071.9084 2119.145)
      (11070.6412 2115.4656) (11068.5649 2110.5038) (11066.4122 2104.5802) (11064.9313 2098.2901) (11064.6718 2092.3664)
      (11065.9237 2087.5573) (11068.7023 2084.5191) (11072.7176 2083.6336) (11077.5115 2084.9466) (11082.5191 2088.1374)
      (11087.2214 2092.5802) (11091.2824 2097.3893) (11094.5344 2101.6641) (11097.084 2104.6107) (11099.2366 2105.6489)
      (11101.3893 2104.6107) (11103.9389 2101.6641) (11107.1908 2097.3893) (11111.2519 2092.5802) (11115.9542 2088.1374)
      (11120.9618 2084.9466) (11125.7557 2083.6336) (11129.771 2084.5191) (11132.5496 2087.5573) (11133.8015 2092.3664)
      (11133.542 2098.2901) (11132.0611 2104.5802) (11129.9084 2110.5038) (11127.8321 2115.4656) (11126.5649 2119.145)
      (11126.7328 2121.5267) (11128.7176 2122.8702) (11132.5344 2123.6031) (11137.8779 2124.2901) (11141.6641 2124.9618)
      (11142.9313 2119.7099) (11147.3282 2107.313) (11152.9771 2095.4351) (11159.7405 2084.3664) (11167.4504 2074.3817)
      (11175.9237 2065.7252) (11184.9313 2058.6107) (11194.2595 2053.2214) (11203.6947 2049.6794) (11212.9771 2048.0611)
      (11221.9084 2048.4275) (11230.2443 2050.7634) (11237.7863 2055.0076) (11244.3664 2061.0687) (11249.8015 2068.7786)
      (11253.9542 2077.9542) (11256.7328 2088.3664) (11258.0763 2099.7557) (11257.9389 2111.8626) (11256.3359 2124.3817)
      (11253.2824 2136.9771) (11248.8855 2149.374) (11243.2366 2161.2519) (11236.4733 2172.3206) (11228.7634 2182.3053)
      (11220.3053 2190.9618) (11211.2977 2198.0763) (11201.9542 2203.4656) (11192.5344 2207.0229) (11183.2366 2208.626)
      (11174.3206 2208.2595) (11165.9695 2205.9237) (11158.4275 2201.6794) (11151.8626 2195.6336) (11146.4275 2187.9237)
      (11142.2595 2178.7481) (11139.4809 2168.3359) (11138.1374 2156.9313) (11138.2137 2150.458) (11137.8779 2150.5191)
      (11132.5344 2151.2061) (11128.7176 2151.9389) (11126.7328 2153.2824) (11126.5649 2155.6641) (11127.8321 2159.3435)
      (11129.9084 2164.3053) (11132.0611 2170.229) (11133.542 2176.5191) (11133.8015 2182.4427) (11132.5496 2187.2519)
      (11129.771 2190.2901) (11125.7557 2191.1756) (11120.9618 2189.8626) (11115.9542 2186.6718) (11111.2519 2182.229)
      (11107.1908 2177.4198) (11103.9389 2173.145) (11101.3893 2170.1985) (11099.2366 2169.1603) (11097.084 2170.1985)
      (11094.5344 2173.145) (11091.2824 2177.4198) (11087.2214 2182.229) (11082.5191 2186.6718) (11081.8321 2187.0992)
      (11079.9542 2185.8473) (11065.3893 2174.5954) (11066.4122 2170.229) (11068.5649 2164.3053) (11070.6412 2159.3435)
      (11071.9084 2155.6641) (11071.7405 2153.2824) (11069.7557 2151.9389) (11065.9389 2151.2061) (11060.5954 2150.5191)
      (11054.4122 2149.4198) (11048.2137 2147.5573) (11042.9466 2144.8092) (11039.4046 2141.3282)
    ))
    ; P3338 -- see feature_dimensions_mm.csv
    ("06_ORNAMENT" 1 (
      (11058.3969 1386.7634) (11065.7863 1394.1527) (11068.8702 1400.1985) (11070.6412 1395.9847) (11071.9084 1392.3053)
      (11071.7405 1389.9237) (11069.7557 1388.5802) (11065.9389 1387.8473) (11060.5954 1387.1603)
    ))
    ; P3339 -- see feature_dimensions_mm.csv
    ("06_ORNAMENT" 1 (
      (11059.542 7374.0458) (11060.9008 7371.5267) (11064.6107 7369.4809) (11069.6489 7368.1527) (11074.7023 7367.4656)
      (11078.4885 7367.0076) (11080.1679 7366.1527) (11079.5725 7364.3511) (11077.2366 7361.3435) (11074.1527 7357.2824)
      (11071.5267 7352.7786) (11070.3511 7348.7176) (11071.1756 7345.9847) (11073.9084 7345.1603) (11077.9695 7346.3359)
      (11082.4733 7348.9618) (11086.5344 7352.0458) (11089.542 7354.3817) (11091.3435 7354.9771) (11092.1985 7353.2977)
      (11092.6565 7349.5115) (11093.3588 7344.458) (11094.6718 7339.4198) (11096.7176 7335.7099) (11099.2366 7334.3511)
      (11101.7557 7335.7099) (11103.8015 7339.4198) (11105.1298 7344.458) (11105.8168 7349.5115) (11106.2748 7353.2977)
      (11107.1298 7354.9771) (11108.9313 7354.3817) (11111.9389 7352.0458) (11116.0 7348.9618) (11120.5038 7346.3359)
      (11124.5649 7345.1603) (11127.2977 7345.9847) (11128.1221 7348.7176) (11126.9466 7352.7786) (11124.3206 7357.2824)
      (11121.2366 7361.3435) (11118.9008 7364.3511) (11118.3053 7366.1527) (11119.9847 7367.0076) (11123.771 7367.4656)
      (11128.8244 7368.1527) (11133.8626 7369.4809) (11137.5725 7371.5267) (11138.9313 7374.0458) (11137.5725 7376.5649)
      (11133.8626 7378.6107) (11128.8244 7379.9237) (11123.771 7380.626) (11119.9847 7381.084) (11118.3053 7381.9389)
      (11118.9008 7383.7405) (11121.2366 7386.7481) (11124.3206 7390.8092) (11126.9466 7395.313) (11128.1221 7399.374)
      (11127.2977 7402.1069) (11124.5649 7402.9313) (11120.5038 7401.7557) (11116.0 7399.1298) (11111.9389 7396.0458)
      (11108.9313 7393.7099) (11107.1298 7393.1145) (11106.2748 7394.7939) (11105.8168 7398.5802) (11105.1298 7403.6336)
      (11103.8015 7408.6718) (11101.7557 7412.3817) (11099.2366 7413.7405) (11096.7176 7412.3817) (11094.6718 7408.6718)
      (11093.3588 7403.6336) (11092.6565 7398.5802) (11092.1985 7394.7939) (11091.3435 7393.1145) (11089.542 7393.7099)
      (11086.5344 7396.0458) (11082.4733 7399.1298) (11077.9695 7401.7557) (11073.9084 7402.9313) (11071.1756 7402.1069)
      (11070.3511 7399.374) (11071.5267 7395.313) (11074.1527 7390.8092) (11077.2366 7386.7481) (11079.5725 7383.7405)
      (11080.1679 7381.9389) (11078.4885 7381.084) (11074.7023 7380.626) (11069.6489 7379.9237) (11064.6107 7378.6107)
      (11060.9008 7376.5649)
    ))
    ; P3340 -- see feature_dimensions_mm.csv
    ("06_ORNAMENT" 1 (
      (11059.542 7206.1069) (11060.9008 7203.5878) (11064.6107 7201.542) (11069.6489 7200.2137) (11074.7023 7199.5267)
      (11078.4885 7199.0687) (11080.1679 7198.2137) (11079.5725 7196.4122) (11077.2366 7193.4046) (11074.1527 7189.3435)
      (11071.5267 7184.8397) (11070.3511 7180.7786) (11071.1756 7178.0458) (11073.9084 7177.2214) (11077.9695 7178.3969)
      (11082.4733 7181.0229) (11086.5344 7184.1069) (11089.542 7186.4427) (11091.3435 7187.0382) (11092.1985 7185.3588)
      (11092.6565 7181.5725) (11093.3588 7176.5191) (11094.6718 7171.4809) (11096.7176 7167.771) (11099.2366 7166.4122)
      (11101.7557 7167.771) (11103.8015 7171.4809) (11105.1298 7176.5191) (11105.8168 7181.5725) (11106.2748 7185.3588)
      (11107.1298 7187.0382) (11108.9313 7186.4427) (11111.9389 7184.1069) (11116.0 7181.0229) (11120.5038 7178.3969)
      (11124.5649 7177.2214) (11127.2977 7178.0458) (11128.1221 7180.7786) (11126.9466 7184.8397) (11124.3206 7189.3435)
      (11121.2366 7193.4046) (11118.9008 7196.4122) (11118.3053 7198.2137) (11119.9847 7199.0687) (11123.771 7199.5267)
      (11128.8244 7200.2137) (11133.8626 7201.542) (11137.5725 7203.5878) (11138.9313 7206.1069) (11137.5725 7208.626)
      (11133.8626 7210.6718) (11128.8244 7211.9847) (11123.771 7212.687) (11119.9847 7213.145) (11118.3053 7214.0)
      (11118.9008 7215.8015) (11121.2366 7218.8092) (11124.3206 7222.8702) (11126.9466 7227.374) (11128.1221 7231.4351)
      (11127.2977 7234.1679) (11124.5649 7234.9924) (11120.5038 7233.8168) (11116.0 7231.1908) (11111.9389 7228.1069)
      (11108.9313 7225.771) (11107.1298 7225.1756) (11106.2748 7226.855) (11105.8168 7230.6412) (11105.1298 7235.6947)
      (11103.8015 7240.7328) (11101.7557 7244.4427) (11099.2366 7245.8015) (11096.7176 7244.4427) (11094.6718 7240.7328)
      (11093.3588 7235.6947) (11092.6565 7230.6412) (11092.1985 7226.855) (11091.3435 7225.1756) (11089.542 7225.771)
      (11086.5344 7228.1069) (11082.4733 7231.1908) (11077.9695 7233.8168) (11073.9084 7234.9924) (11071.1756 7234.1679)
      (11070.3511 7231.4351) (11071.5267 7227.374) (11074.1527 7222.8702) (11077.2366 7218.8092) (11079.5725 7215.8015)
      (11080.1679 7214.0) (11078.4885 7213.145) (11074.7023 7212.687) (11069.6489 7211.9847) (11064.6107 7210.6718)
      (11060.9008 7208.626)
    ))
    ; P3341 -- see feature_dimensions_mm.csv
    ("06_ORNAMENT" 1 (
      (11064.1832 1986.0458) (11064.9313 1970.855) (11068.3817 1954.5191) (11074.4733 1937.4198) (11083.0534 1920.0)
      (11093.8931 1902.6718) (11106.7481 1885.8626) (11121.2824 1870.0) (11137.145 1855.4656) (11153.9389 1842.626)
      (11171.2672 1831.771) (11188.7023 1823.2061) (11205.7863 1817.1145) (11222.1374 1813.6489) (11237.313 1812.9008)
      (11250.9771 1814.9008) (11262.7786 1819.5725) (11272.4122 1826.8244) (11279.6641 1836.458) (11284.3359 1848.2595)
      (11286.3359 1861.9237) (11285.5878 1877.0992) (11282.1221 1893.4504) (11276.0305 1910.5344) (11267.4656 1927.9695)
      (11256.6107 1945.2977) (11243.771 1962.0916) (11229.2366 1977.9542) (11213.374 1992.4885) (11196.5649 2005.3435)
      (11179.2366 2016.1832) (11161.8168 2024.7634) (11144.7176 2030.855) (11128.3817 2034.3053) (11113.1908 2035.0534)
      (11099.5267 2033.0687) (11087.7405 2028.3817) (11078.0916 2021.145) (11070.855 2011.4962) (11066.1679 1999.7099)
    ))
    ; P3342 -- see feature_dimensions_mm.csv
    ("06_ORNAMENT" 1 (
      (11064.1832 1494.8702) (11066.1679 1481.2061) (11070.855 1469.4198) (11078.0916 1459.771) (11087.7405 1452.5191)
      (11099.5267 1447.8473) (11113.1908 1445.8626) (11128.3817 1446.5954) (11144.7176 1450.0611) (11161.8168 1456.1527)
      (11179.2366 1464.7328) (11196.5649 1475.5725) (11213.374 1488.4275) (11229.2366 1502.9618) (11243.771 1518.8244)
      (11256.6107 1535.6183) (11267.4656 1552.9466) (11276.0305 1570.3817) (11282.1221 1587.4656) (11285.5878 1603.8168)
      (11286.3359 1618.9924) (11284.3359 1632.6565) (11279.6641 1644.458) (11272.4122 1654.0916) (11262.7786 1661.3435)
      (11250.9771 1666.0153) (11237.313 1668.0153) (11222.1374 1667.2672) (11205.7863 1663.8015) (11188.7023 1657.7099)
      (11171.2672 1649.145) (11153.9389 1638.2901) (11137.145 1625.4504) (11121.2824 1610.916) (11106.7481 1595.0534)
      (11093.8931 1578.2443) (11083.0534 1560.916) (11074.4733 1543.4962) (11068.3817 1526.3969) (11064.9313 1510.0611)
    ))
    ; P3343 -- see feature_dimensions_mm.csv
    ("06_ORNAMENT" 1 (
      (11078.4733 3007.6336) (11079.1908 3006.3206) (11081.1145 3005.2519) (11083.7557 3004.5496) (11086.3969 3004.1985)
      (11088.3817 3003.9542) (11089.2672 3003.4962) (11088.9618 3002.5649) (11087.7252 3000.9924) (11086.1221 2998.8702)
      (11084.7481 2996.5038) (11084.1221 2994.3817) (11084.5496 2992.9466) (11085.9847 2992.5191) (11088.1069 2993.145)
      (11090.4733 2994.5191) (11092.5954 2996.1221) (11094.1679 2997.3588) (11095.0992 2997.6641) (11095.5573 2996.7786)
      (11095.8015 2994.7939) (11096.1527 2992.1527) (11096.855 2989.5115) (11097.9237 2987.5878) (11099.2366 2986.8702)
      (11100.5496 2987.5878) (11101.6183 2989.5115) (11102.3206 2992.1527) (11102.6718 2994.7939) (11102.916 2996.7786)
      (11103.374 2997.6641) (11104.3053 2997.3588) (11105.8779 2996.1221) (11108.0 2994.5191) (11110.3664 2993.145)
      (11112.4885 2992.5191) (11113.9237 2992.9466) (11114.3511 2994.3817) (11113.7252 2996.5038) (11112.3511 2998.8702)
      (11110.7481 3000.9924) (11109.5115 3002.5649) (11109.2061 3003.4962) (11110.0916 3003.9542) (11112.0763 3004.1985)
      (11114.7176 3004.5496) (11117.3588 3005.2519) (11119.2824 3006.3206) (11120.0 3007.6336) (11119.2824 3008.9466)
      (11117.3588 3010.0153) (11114.7176 3010.7176) (11112.0763 3011.0687) (11110.0916 3011.313) (11109.2061 3011.771)
      (11109.5115 3012.7023) (11110.7481 3014.2748) (11112.3511 3016.3969) (11113.7252 3018.7634) (11114.3511 3020.8855)
      (11113.9237 3022.3206) (11112.4885 3022.7481) (11110.3664 3022.1221) (11108.0 3020.7481) (11105.8779 3019.145)
      (11104.3053 3017.9084) (11103.374 3017.6031) (11102.916 3018.4885) (11102.6718 3020.4733) (11102.3206 3023.1145)
      (11101.6183 3025.7557) (11100.5496 3027.6794) (11099.2366 3028.3969) (11097.9237 3027.6794) (11096.855 3025.7557)
      (11096.1527 3023.1145) (11095.8015 3020.4733) (11095.5573 3018.4885) (11095.0992 3017.6031) (11094.1679 3017.9084)
      (11092.5954 3019.145) (11090.4733 3020.7481) (11088.1069 3022.1221) (11085.9847 3022.7481) (11084.5496 3022.3206)
      (11084.1221 3020.8855) (11084.7481 3018.7634) (11086.1221 3016.3969) (11087.7252 3014.2748) (11088.9618 3012.7023)
      (11089.2672 3011.771) (11088.3817 3011.313) (11086.3969 3011.0687) (11083.7557 3010.7176) (11081.1145 3010.0153)
      (11079.1908 3008.9466)
    ))
    ; P3344 -- see feature_dimensions_mm.csv
    ("06_ORNAMENT" 1 (
      (11078.4733 2900.7634) (11079.1908 2899.4504) (11081.1145 2898.3817) (11083.7557 2897.6794) (11086.3969 2897.3282)
      (11088.3817 2897.084) (11089.2672 2896.626) (11088.9618 2895.6947) (11087.7252 2894.1221) (11086.1221 2892.0)
      (11084.7481 2889.6336) (11084.1221 2887.5115) (11084.5496 2886.0763) (11085.9847 2885.6489) (11088.1069 2886.2748)
      (11090.4733 2887.6489) (11092.5954 2889.2519) (11094.1679 2890.4885) (11095.0992 2890.7939) (11095.5573 2889.9084)
      (11095.8015 2887.9237) (11096.1527 2885.2824) (11096.855 2882.6412) (11097.9237 2880.7176) (11099.2366 2880.0)
      (11100.5496 2880.7176) (11101.6183 2882.6412) (11102.3206 2885.2824) (11102.6718 2887.9237) (11102.916 2889.9084)
      (11103.374 2890.7939) (11104.3053 2890.4885) (11105.8779 2889.2519) (11108.0 2887.6489) (11110.3664 2886.2748)
      (11112.4885 2885.6489) (11113.9237 2886.0763) (11114.3511 2887.5115) (11113.7252 2889.6336) (11112.3511 2892.0)
      (11110.7481 2894.1221) (11109.5115 2895.6947) (11109.2061 2896.626) (11110.0916 2897.084) (11112.0763 2897.3282)
      (11114.7176 2897.6794) (11117.3588 2898.3817) (11119.2824 2899.4504) (11120.0 2900.7634) (11119.2824 2902.0763)
      (11117.3588 2903.145) (11114.7176 2903.8473) (11112.0763 2904.1985) (11110.0916 2904.4427) (11109.2061 2904.9008)
      (11109.5115 2905.8321) (11110.7481 2907.4046) (11112.3511 2909.5267) (11113.7252 2911.8931) (11114.3511 2914.0153)
      (11113.9237 2915.4504) (11112.4885 2915.8779) (11110.3664 2915.2519) (11108.0 2913.8779) (11105.8779 2912.2748)
      (11104.3053 2911.0382) (11103.374 2910.7328) (11102.916 2911.6183) (11102.6718 2913.6031) (11102.3206 2916.2443)
      (11101.6183 2918.8855) (11100.5496 2920.8092) (11099.2366 2921.5267) (11097.9237 2920.8092) (11096.855 2918.8855)
      (11096.1527 2916.2443) (11095.8015 2913.6031) (11095.5573 2911.6183) (11095.0992 2910.7328) (11094.1679 2911.0382)
      (11092.5954 2912.2748) (11090.4733 2913.8779) (11088.1069 2915.2519) (11085.9847 2915.8779) (11084.5496 2915.4504)
      (11084.1221 2914.0153) (11084.7481 2911.8931) (11086.1221 2909.5267) (11087.7252 2907.4046) (11088.9618 2905.8321)
      (11089.2672 2904.9008) (11088.3817 2904.4427) (11086.3969 2904.1985) (11083.7557 2903.8473) (11081.1145 2903.145)
      (11079.1908 2902.0763)
    ))
    ; P3345 -- see feature_dimensions_mm.csv
    ("06_ORNAMENT" 1 (
      (11090.1069 7374.0458) (11090.8092 7370.5496) (11092.7786 7367.5878) (11095.7405 7365.6183) (11099.2366 7364.916)
      (11102.7328 7365.6183) (11105.6947 7367.5878) (11107.6641 7370.5496) (11108.3664 7374.0458) (11107.6641 7377.542)
      (11105.6947 7380.5038) (11102.7328 7382.4733) (11099.2366 7383.1756) (11095.7405 7382.4733) (11092.7786 7380.5038)
      (11090.8092 7377.542)
    ))
    ; P3346 -- see feature_dimensions_mm.csv
    ("06_ORNAMENT" 1 (
      (11090.1069 7206.1069) (11090.8092 7202.6107) (11092.7786 7199.6489) (11095.7405 7197.6794) (11099.2366 7196.9771)
      (11102.7328 7197.6794) (11105.6947 7199.6489) (11107.6641 7202.6107) (11108.3664 7206.1069) (11107.6641 7209.6031)
      (11105.6947 7212.5649) (11102.7328 7214.5344) (11099.2366 7215.2366) (11095.7405 7214.5344) (11092.7786 7212.5649)
      (11090.8092 7209.6031)
    ))
    ; P3347 -- see feature_dimensions_mm.csv
    ("06_ORNAMENT" 1 (
      (11093.1298 3007.6336) (11093.5878 3005.2977) (11094.916 3003.313) (11096.9008 3001.9847) (11099.2366 3001.5267)
      (11101.5725 3001.9847) (11103.5573 3003.313) (11104.8855 3005.2977) (11105.3435 3007.6336) (11104.8855 3009.9695)
      (11103.5573 3011.9542) (11101.5725 3013.2824) (11099.2366 3013.7405) (11096.9008 3013.2824) (11094.916 3011.9542)
      (11093.5878 3009.9695)
    ))
    ; P3348 -- see feature_dimensions_mm.csv
    ("06_ORNAMENT" 1 (
      (11093.1298 2900.7634) (11093.5878 2898.4275) (11094.916 2896.4427) (11096.9008 2895.1145) (11099.2366 2894.6565)
      (11101.5725 2895.1145) (11103.5573 2896.4427) (11104.8855 2898.4275) (11105.3435 2900.7634) (11104.8855 2903.0992)
      (11103.5573 2905.084) (11101.5725 2906.4122) (11099.2366 2906.8702) (11096.9008 2906.4122) (11094.916 2905.084)
      (11093.5878 2903.0992)
    ))
    ; P3349 -- see feature_dimensions_mm.csv
    ("06_ORNAMENT" 1 (
      (11251.9084 1740.458) (11253.9695 1719.6031) (11260.0458 1699.5573) (11269.9237 1681.084) (11283.2061 1664.8855)
      (11299.4046 1651.6031) (11317.8779 1641.7252) (11337.9237 1635.6336) (11358.7786 1633.5878) (11379.6336 1635.6336)
      (11399.6794 1641.7252) (11418.1527 1651.6031) (11434.3511 1664.8855) (11447.6336 1681.084) (11457.5115 1699.5573)
      (11463.6031 1719.6031) (11465.6489 1740.458) (11463.6031 1761.313) (11457.5115 1781.3588) (11447.6336 1799.8321)
      (11434.3511 1816.0305) (11418.1527 1829.313) (11399.6794 1839.1908) (11379.6336 1845.2672) (11358.7786 1847.3282)
      (11337.9237 1845.2672) (11317.8779 1839.1908) (11299.4046 1829.313) (11283.2061 1816.0305) (11269.9237 1799.8321)
      (11260.0458 1781.3588) (11253.9695 1761.313)
    ))
    ; P3350 -- see feature_dimensions_mm.csv
    ("06_ORNAMENT" 1 (
      (11282.4427 2000.0) (11283.3893 1978.5038) (11286.1832 1957.542) (11290.7634 1937.6183) (11297.0229 1919.2366)
      (11304.7939 1902.8397) (11313.9084 1888.8397) (11324.1221 1877.5725) (11335.1908 1869.313) (11346.8397 1864.2901)
      (11358.7786 1862.5954) (11370.7176 1864.2901) (11382.3664 1869.313) (11393.4351 1877.5725) (11403.6489 1888.8397)
      (11412.7634 1902.8397) (11420.5344 1919.2366) (11426.7939 1937.6183) (11431.374 1957.542) (11434.1679 1978.5038)
      (11435.1145 2000.0) (11434.1679 2021.4962) (11431.374 2042.458) (11426.7939 2062.3817) (11420.5344 2080.7634)
      (11412.7634 2097.1603) (11403.6489 2111.1603) (11393.4351 2122.4275) (11382.3664 2130.687) (11370.7176 2135.7099)
      (11358.7786 2137.4046) (11346.8397 2135.7099) (11335.1908 2130.687) (11324.1221 2122.4275) (11313.9084 2111.1603)
      (11304.7939 2097.1603) (11297.0229 2080.7634) (11290.7634 2062.3817) (11286.1832 2042.458) (11283.3893 2021.4962)
    ))
    ; P3351 -- see feature_dimensions_mm.csv
    ("06_ORNAMENT" 1 (
      (11282.4427 1740.458) (11283.9084 1725.5725) (11288.2595 1711.2519) (11295.313 1698.0458) (11304.7939 1686.4733)
      (11316.3664 1676.9924) (11329.5725 1669.9389) (11343.8931 1665.5878) (11358.7786 1664.1221) (11373.6641 1665.5878)
      (11387.9847 1669.9389) (11401.1908 1676.9924) (11412.7634 1686.4733) (11422.2443 1698.0458) (11429.2977 1711.2519)
      (11433.6489 1725.5725) (11435.1145 1740.458) (11433.6489 1755.3435) (11429.2977 1769.6641) (11422.2443 1782.8702)
      (11412.7634 1794.4427) (11401.1908 1803.9237) (11387.9847 1810.9771) (11373.6641 1815.3282) (11358.7786 1816.7939)
      (11343.8931 1815.3282) (11329.5725 1810.9771) (11316.3664 1803.9237) (11304.7939 1794.4427) (11295.313 1782.8702)
      (11288.2595 1769.6641) (11283.9084 1755.3435)
    ))
    ; P3352 -- see feature_dimensions_mm.csv
    ("06_ORNAMENT" 1 (
      (11282.4427 1480.916) (11283.3893 1459.4198) (11286.1832 1438.458) (11290.7634 1418.5344) (11297.0229 1400.1527)
      (11304.7939 1383.7557) (11313.9084 1369.7557) (11324.1221 1358.4885) (11335.1908 1350.229) (11346.8397 1345.2061)
      (11358.7786 1343.5115) (11370.7176 1345.2061) (11382.3664 1350.229) (11393.4351 1358.4885) (11403.6489 1369.7557)
      (11412.7634 1383.7557) (11420.5344 1400.1527) (11426.7939 1418.5344) (11431.374 1438.458) (11434.1679 1459.4198)
      (11435.1145 1480.916) (11434.1679 1502.4122) (11431.374 1523.374) (11426.7939 1543.2977) (11420.5344 1561.6794)
      (11412.7634 1578.0763) (11403.6489 1592.0763) (11393.4351 1603.3435) (11382.3664 1611.6031) (11370.7176 1616.626)
      (11358.7786 1618.3206) (11346.8397 1616.626) (11335.1908 1611.6031) (11324.1221 1603.3435) (11313.9084 1592.0763)
      (11304.7939 1578.0763) (11297.0229 1561.6794) (11290.7634 1543.2977) (11286.1832 1523.374) (11283.3893 1502.4122)
    ))
    ; P3353 -- see feature_dimensions_mm.csv
    ("06_ORNAMENT" 1 (
      (11320.6107 2198.4733) (11322.4733 2186.6718) (11327.8931 2176.0458) (11336.3511 2167.5878) (11346.9771 2162.1679)
      (11358.7786 2160.3053) (11370.5802 2162.1679) (11381.2061 2167.5878) (11389.6641 2176.0458) (11395.084 2186.6718)
      (11396.9466 2198.4733) (11395.084 2210.2748) (11389.6641 2220.9008) (11381.2061 2229.3588) (11370.5802 2234.7786)
      (11358.7786 2236.6412) (11346.9771 2234.7786) (11336.3511 2229.3588) (11327.8931 2220.9008) (11322.4733 2210.2748)
    ))
    ; P3354 -- see feature_dimensions_mm.csv
    ("06_ORNAMENT" 1 (
      (11320.6107 1282.4427) (11322.4733 1270.6412) (11327.8931 1260.0153) (11336.3511 1251.5573) (11346.9771 1246.1374)
      (11358.7786 1244.2748) (11370.5802 1246.1374) (11381.2061 1251.5573) (11389.6641 1260.0153) (11395.084 1270.6412)
      (11396.9466 1282.4427) (11395.084 1294.2443) (11389.6641 1304.8702) (11381.2061 1313.3282) (11370.5802 1318.7481)
      (11358.7786 1320.6107) (11346.9771 1318.7481) (11336.3511 1313.3282) (11327.8931 1304.8702) (11322.4733 1294.2443)
    ))
    ; P3355 -- see feature_dimensions_mm.csv
    ("06_ORNAMENT" 1 (
      (11346.5649 6135.8779) (11349.2366 6137.1908) (11354.2595 6138.3664) (11361.0229 6139.3282) (11368.9008 6139.9847)
      (11377.2672 6140.2137) (11385.5267 6139.9237) (11393.0534 6139.0229) (11399.2366 6137.4046) (11404.5954 6134.9466)
      (11409.9389 6131.6947) (11415.084 6127.7863) (11419.8473 6123.374) (11424.0458 6118.626) (11427.4656 6113.6794)
      (11429.9542 6108.687) (11431.2977 6103.8168) (11431.7405 6098.8092) (11431.5725 6093.4198) (11430.6412 6087.7863)
      (11428.8702 6082.0611) (11426.0916 6076.3817) (11422.229 6070.9008) (11420.7939 6069.4504) (11418.8855 6070.1985)
      (11383.145 6082.3664) (11353.1603 6091.2977) (11356.3511 6092.7023) (11362.0916 6096.1679) (11367.313 6100.1832)
      (11371.8168 6104.4733) (11375.3588 6108.7328) (11377.6947 6112.6718) (11378.626 6116.0305) (11377.2214 6119.0076)
      (11373.2977 6121.9542) (11367.7405 6124.8397) (11361.4504 6127.5725) (11355.2977 6130.1069) (11350.1832 6132.3817)
      (11346.9771 6134.3206)
    ))
    ; P3356 -- see feature_dimensions_mm.csv
    ("06_ORNAMENT" 1 (
      (11353.2824 3007.6336) (11354.0 3006.3206) (11355.9237 3005.2519) (11358.5649 3004.5496) (11361.2061 3004.1985)
      (11363.1908 3003.9542) (11364.0763 3003.4962) (11363.771 3002.5649) (11362.5344 3000.9924) (11360.9313 2998.8702)
      (11359.5573 2996.5038) (11358.9313 2994.3817) (11359.3588 2992.9466) (11360.7939 2992.5191) (11362.916 2993.145)
      (11365.2824 2994.5191) (11367.4046 2996.1221) (11368.9771 2997.3588) (11369.9084 2997.6641) (11370.3664 2996.7786)
      (11370.6107 2994.7939) (11370.9618 2992.1527) (11371.6641 2989.5115) (11372.7328 2987.5878) (11374.0458 2986.8702)
      (11375.3588 2987.5878) (11376.4275 2989.5115) (11377.1298 2992.1527) (11377.4809 2994.7939) (11377.7252 2996.7786)
      (11378.1832 2997.6641) (11379.1145 2997.3588) (11380.687 2996.1221) (11382.8092 2994.5191) (11385.1756 2993.145)
      (11387.2977 2992.5191) (11388.7328 2992.9466) (11389.1603 2994.3817) (11388.5344 2996.5038) (11387.1603 2998.8702)
      (11385.5573 3000.9924) (11384.3206 3002.5649) (11384.0153 3003.4962) (11384.9008 3003.9542) (11386.8855 3004.1985)
      (11389.5267 3004.5496) (11392.1679 3005.2519) (11394.0916 3006.3206) (11394.8092 3007.6336) (11394.0916 3008.9466)
      (11392.1679 3010.0153) (11389.5267 3010.7176) (11386.8855 3011.0687) (11384.9008 3011.313) (11384.0153 3011.771)
      (11384.3206 3012.7023) (11385.5573 3014.2748) (11387.1603 3016.3969) (11388.5344 3018.7634) (11389.1603 3020.8855)
      (11388.7328 3022.3206) (11387.2977 3022.7481) (11385.1756 3022.1221) (11382.8092 3020.7481) (11380.687 3019.145)
      (11379.1145 3017.9084) (11378.1832 3017.6031) (11377.7252 3018.4885) (11377.4809 3020.4733) (11377.1298 3023.1145)
      (11376.4275 3025.7557) (11375.3588 3027.6794) (11374.0458 3028.3969) (11372.7328 3027.6794) (11371.6641 3025.7557)
      (11370.9618 3023.1145) (11370.6107 3020.4733) (11370.3664 3018.4885) (11369.9084 3017.6031) (11368.9771 3017.9084)
      (11367.4046 3019.145) (11365.2824 3020.7481) (11362.916 3022.1221) (11360.7939 3022.7481) (11359.3588 3022.3206)
      (11358.9313 3020.8855) (11359.5573 3018.7634) (11360.9313 3016.3969) (11362.5344 3014.2748) (11363.771 3012.7023)
      (11364.0763 3011.771) (11363.1908 3011.313) (11361.2061 3011.0687) (11358.5649 3010.7176) (11355.9237 3010.0153)
      (11354.0 3008.9466)
    ))
    ; P3357 -- see feature_dimensions_mm.csv
    ("06_ORNAMENT" 1 (
      (11353.2824 2900.7634) (11354.0 2899.4504) (11355.9237 2898.3817) (11358.5649 2897.6794) (11361.2061 2897.3282)
      (11363.1908 2897.084) (11364.0763 2896.626) (11363.771 2895.6947) (11362.5344 2894.1221) (11360.9313 2892.0)
      (11359.5573 2889.6336) (11358.9313 2887.5115) (11359.3588 2886.0763) (11360.7939 2885.6489) (11362.916 2886.2748)
      (11365.2824 2887.6489) (11367.4046 2889.2519) (11368.9771 2890.4885) (11369.9084 2890.7939) (11370.3664 2889.9084)
      (11370.6107 2887.9237) (11370.9618 2885.2824) (11371.6641 2882.6412) (11372.7328 2880.7176) (11374.0458 2880.0)
      (11375.3588 2880.7176) (11376.4275 2882.6412) (11377.1298 2885.2824) (11377.4809 2887.9237) (11377.7252 2889.9084)
      (11378.1832 2890.7939) (11379.1145 2890.4885) (11380.687 2889.2519) (11382.8092 2887.6489) (11385.1756 2886.2748)
      (11387.2977 2885.6489) (11388.7328 2886.0763) (11389.1603 2887.5115) (11388.5344 2889.6336) (11387.1603 2892.0)
      (11385.5573 2894.1221) (11384.3206 2895.6947) (11384.0153 2896.626) (11384.9008 2897.084) (11386.8855 2897.3282)
      (11389.5267 2897.6794) (11392.1679 2898.3817) (11394.0916 2899.4504) (11394.8092 2900.7634) (11394.0916 2902.0763)
      (11392.1679 2903.145) (11389.5267 2903.8473) (11386.8855 2904.1985) (11384.9008 2904.4427) (11384.0153 2904.9008)
      (11384.3206 2905.8321) (11385.5573 2907.4046) (11387.1603 2909.5267) (11388.5344 2911.8931) (11389.1603 2914.0153)
      (11388.7328 2915.4504) (11387.2977 2915.8779) (11385.1756 2915.2519) (11382.8092 2913.8779) (11380.687 2912.2748)
      (11379.1145 2911.0382) (11378.1832 2910.7328) (11377.7252 2911.6183) (11377.4809 2913.6031) (11377.1298 2916.2443)
      (11376.4275 2918.8855) (11375.3588 2920.8092) (11374.0458 2921.5267) (11372.7328 2920.8092) (11371.6641 2918.8855)
      (11370.9618 2916.2443) (11370.6107 2913.6031) (11370.3664 2911.6183) (11369.9084 2910.7328) (11368.9771 2911.0382)
      (11367.4046 2912.2748) (11365.2824 2913.8779) (11362.916 2915.2519) (11360.7939 2915.8779) (11359.3588 2915.4504)
      (11358.9313 2914.0153) (11359.5573 2911.8931) (11360.9313 2909.5267) (11362.5344 2907.4046) (11363.771 2905.8321)
      (11364.0763 2904.9008) (11363.1908 2904.4427) (11361.2061 2904.1985) (11358.5649 2903.8473) (11355.9237 2903.145)
      (11354.0 2902.0763)
    ))
    ; P3358 -- see feature_dimensions_mm.csv
    ("06_ORNAMENT" 1 (
      (11364.1221 5275.0687) (11365.3435 5268.9313) (11368.8244 5263.7252) (11374.0153 5260.2595) (11380.1527 5259.0382)
      (11386.2901 5260.2595) (11391.4809 5263.7252) (11394.9618 5268.9313) (11396.1832 5275.0687) (11394.9618 5281.2061)
      (11391.4809 5286.3969) (11386.2901 5289.8779) (11380.1527 5291.0992) (11374.0153 5289.8779) (11368.8244 5286.3969)
      (11365.3435 5281.2061)
    ))
    ; P3359 -- see feature_dimensions_mm.csv
    ("06_ORNAMENT" 1 (
      (11364.1221 5198.7328) (11365.3435 5192.5954) (11368.8244 5187.3893) (11374.0153 5183.9237) (11380.1527 5182.7023)
      (11386.2901 5183.9237) (11391.4809 5187.3893) (11394.9618 5192.5954) (11396.1832 5198.7328) (11394.9618 5204.8702)
      (11391.4809 5210.0611) (11386.2901 5213.542) (11380.1527 5214.7634) (11374.0153 5213.542) (11368.8244 5210.0611)
      (11365.3435 5204.8702)
    ))
    ; P3360 -- see feature_dimensions_mm.csv
    ("06_ORNAMENT" 1 (
      (11364.1221 5122.3969) (11365.3435 5116.2595) (11368.8244 5111.0534) (11374.0153 5107.5878) (11380.1527 5106.3664)
      (11386.2901 5107.5878) (11391.4809 5111.0534) (11394.9618 5116.2595) (11396.1832 5122.3969) (11394.9618 5128.5344)
      (11391.4809 5133.7252) (11386.2901 5137.2061) (11380.1527 5138.4275) (11374.0153 5137.2061) (11368.8244 5133.7252)
      (11365.3435 5128.5344)
    ))
    ; P3361 -- see feature_dimensions_mm.csv
    ("06_ORNAMENT" 1 (
      (11364.1221 5046.0611) (11365.3435 5039.9237) (11368.8244 5034.7176) (11374.0153 5031.2519) (11380.1527 5030.0305)
      (11386.2901 5031.2519) (11391.4809 5034.7176) (11394.9618 5039.9237) (11396.1832 5046.0611) (11394.9618 5052.1985)
      (11391.4809 5057.3893) (11386.2901 5060.8702) (11380.1527 5062.0916) (11374.0153 5060.8702) (11368.8244 5057.3893)
      (11365.3435 5052.1985)
    ))
    ; P3362 -- see feature_dimensions_mm.csv
    ("06_ORNAMENT" 1 (
      (11364.1221 4969.7252) (11365.3435 4963.5878) (11368.8244 4958.3817) (11374.0153 4954.916) (11380.1527 4953.6947)
      (11386.2901 4954.916) (11391.4809 4958.3817) (11394.9618 4963.5878) (11396.1832 4969.7252) (11394.9618 4975.8626)
      (11391.4809 4981.0534) (11386.2901 4984.5344) (11380.1527 4985.7557) (11374.0153 4984.5344) (11368.8244 4981.0534)
      (11365.3435 4975.8626)
    ))
    ; P3363 -- see feature_dimensions_mm.csv
    ("06_ORNAMENT" 1 (
      (11364.1221 4893.3893) (11365.3435 4887.2519) (11368.8244 4882.0458) (11374.0153 4878.5802) (11380.1527 4877.3588)
      (11386.2901 4878.5802) (11391.4809 4882.0458) (11394.9618 4887.2519) (11396.1832 4893.3893) (11394.9618 4899.5267)
      (11391.4809 4904.7176) (11386.2901 4908.1985) (11380.1527 4909.4198) (11374.0153 4908.1985) (11368.8244 4904.7176)
      (11365.3435 4899.5267)
    ))
    ; P3364 -- see feature_dimensions_mm.csv
    ("06_ORNAMENT" 1 (
      (11364.1221 4817.0534) (11365.3435 4810.916) (11368.8244 4805.7099) (11374.0153 4802.2443) (11380.1527 4801.0229)
      (11386.2901 4802.2443) (11391.4809 4805.7099) (11394.9618 4810.916) (11396.1832 4817.0534) (11394.9618 4823.1908)
      (11391.4809 4828.3817) (11386.2901 4831.8626) (11380.1527 4833.084) (11374.0153 4831.8626) (11368.8244 4828.3817)
      (11365.3435 4823.1908)
    ))
    ; P3365 -- see feature_dimensions_mm.csv
    ("06_ORNAMENT" 1 (
      (11364.1221 4664.3817) (11365.3435 4658.2443) (11368.8244 4653.0382) (11374.0153 4649.5725) (11380.1527 4648.3511)
      (11386.2901 4649.5725) (11391.4809 4653.0382) (11394.9618 4658.2443) (11396.1832 4664.3817) (11394.9618 4670.5191)
      (11391.4809 4675.7099) (11386.2901 4679.1908) (11380.1527 4680.4122) (11374.0153 4679.1908) (11368.8244 4675.7099)
      (11365.3435 4670.5191)
    ))
    ; P3366 -- see feature_dimensions_mm.csv
    ("06_ORNAMENT" 1 (
      (11364.1221 4588.0458) (11365.3435 4581.9084) (11368.8244 4576.7023) (11374.0153 4573.2366) (11380.1527 4572.0153)
      (11386.2901 4573.2366) (11391.4809 4576.7023) (11394.9618 4581.9084) (11396.1832 4588.0458) (11394.9618 4594.1832)
      (11391.4809 4599.374) (11386.2901 4602.855) (11380.1527 4604.0763) (11374.0153 4602.855) (11368.8244 4599.374)
      (11365.3435 4594.1832)
    ))
    ; P3367 -- see feature_dimensions_mm.csv
    ("06_ORNAMENT" 1 (
      (11364.1221 4511.7099) (11365.3435 4505.5725) (11368.8244 4500.3664) (11374.0153 4496.9008) (11380.1527 4495.6794)
      (11386.2901 4496.9008) (11391.4809 4500.3664) (11394.9618 4505.5725) (11396.1832 4511.7099) (11394.9618 4517.8473)
      (11391.4809 4523.0382) (11386.2901 4526.5191) (11380.1527 4527.7405) (11374.0153 4526.5191) (11368.8244 4523.0382)
      (11365.3435 4517.8473)
    ))
    ; P3368 -- see feature_dimensions_mm.csv
    ("06_ORNAMENT" 1 (
      (11364.1221 4359.0382) (11365.3435 4352.9008) (11368.8244 4347.6947) (11374.0153 4344.229) (11380.1527 4343.0076)
      (11386.2901 4344.229) (11391.4809 4347.6947) (11394.9618 4352.9008) (11396.1832 4359.0382) (11394.9618 4365.1756)
      (11391.4809 4370.3664) (11386.2901 4373.8473) (11380.1527 4375.0687) (11374.0153 4373.8473) (11368.8244 4370.3664)
      (11365.3435 4365.1756)
    ))
    ; P3369 -- see feature_dimensions_mm.csv
    ("06_ORNAMENT" 1 (
      (11364.1221 4282.7023) (11365.3435 4276.5649) (11368.8244 4271.3588) (11374.0153 4267.8931) (11380.1527 4266.6718)
      (11386.2901 4267.8931) (11391.4809 4271.3588) (11394.9618 4276.5649) (11396.1832 4282.7023) (11394.9618 4288.8397)
      (11391.4809 4294.0305) (11386.2901 4297.5115) (11380.1527 4298.7328) (11374.0153 4297.5115) (11368.8244 4294.0305)
      (11365.3435 4288.8397)
    ))
    ; P3370 -- see feature_dimensions_mm.csv
    ("06_ORNAMENT" 1 (
      (11364.1221 4206.3664) (11365.3435 4200.229) (11368.8244 4195.0229) (11374.0153 4191.5573) (11380.1527 4190.3359)
      (11386.2901 4191.5573) (11391.4809 4195.0229) (11394.9618 4200.229) (11396.1832 4206.3664) (11394.9618 4212.5038)
      (11391.4809 4217.6947) (11386.2901 4221.1756) (11380.1527 4222.3969) (11374.0153 4221.1756) (11368.8244 4217.6947)
      (11365.3435 4212.5038)
    ))
    ; P3371 -- see feature_dimensions_mm.csv
    ("06_ORNAMENT" 1 (
      (11364.1221 4053.6947) (11365.3435 4047.5573) (11368.8244 4042.3511) (11374.0153 4038.8855) (11380.1527 4037.6641)
      (11386.2901 4038.8855) (11391.4809 4042.3511) (11394.9618 4047.5573) (11396.1832 4053.6947) (11394.9618 4059.8321)
      (11391.4809 4065.0229) (11386.2901 4068.5038) (11380.1527 4069.7252) (11374.0153 4068.5038) (11368.8244 4065.0229)
      (11365.3435 4059.8321)
    ))
    ; P3372 -- see feature_dimensions_mm.csv
    ("06_ORNAMENT" 1 (
      (11364.1221 3977.3588) (11365.3435 3971.2214) (11368.8244 3966.0153) (11374.0153 3962.5496) (11380.1527 3961.3282)
      (11386.2901 3962.5496) (11391.4809 3966.0153) (11394.9618 3971.2214) (11396.1832 3977.3588) (11394.9618 3983.4962)
      (11391.4809 3988.687) (11386.2901 3992.1679) (11380.1527 3993.3893) (11374.0153 3992.1679) (11368.8244 3988.687)
      (11365.3435 3983.4962)
    ))
    ; P3373 -- see feature_dimensions_mm.csv
    ("06_ORNAMENT" 1 (
      (11364.1221 3901.0229) (11365.3435 3894.8855) (11368.8244 3889.6794) (11374.0153 3886.2137) (11380.1527 3884.9924)
      (11386.2901 3886.2137) (11391.4809 3889.6794) (11394.9618 3894.8855) (11396.1832 3901.0229) (11394.9618 3907.1603)
      (11391.4809 3912.3511) (11386.2901 3915.8321) (11380.1527 3917.0534) (11374.0153 3915.8321) (11368.8244 3912.3511)
      (11365.3435 3907.1603)
    ))
    ; P3374 -- see feature_dimensions_mm.csv
    ("06_ORNAMENT" 1 (
      (11367.9389 3007.6336) (11368.3969 3005.2977) (11369.7252 3003.313) (11371.7099 3001.9847) (11374.0458 3001.5267)
      (11376.3817 3001.9847) (11378.3664 3003.313) (11379.6947 3005.2977) (11380.1527 3007.6336) (11379.6947 3009.9695)
      (11378.3664 3011.9542) (11376.3817 3013.2824) (11374.0458 3013.7405) (11371.7099 3013.2824) (11369.7252 3011.9542)
      (11368.3969 3009.9695)
    ))
    ; P3375 -- see feature_dimensions_mm.csv
    ("06_ORNAMENT" 1 (
      (11367.9389 2900.7634) (11368.3969 2898.4275) (11369.7252 2896.4427) (11371.7099 2895.1145) (11374.0458 2894.6565)
      (11376.3817 2895.1145) (11378.3664 2896.4427) (11379.6947 2898.4275) (11380.1527 2900.7634) (11379.6947 2903.0992)
      (11378.3664 2905.084) (11376.3817 2906.4122) (11374.0458 2906.8702) (11371.7099 2906.4122) (11369.7252 2905.084)
      (11368.3969 2903.0992)
    ))
    ; P3376 -- see feature_dimensions_mm.csv
    ("06_ORNAMENT" 1 (
      (11403.5573 5312.9771) (11405.0687 5307.313) (11409.2214 5303.1603) (11414.8855 5301.6336) (11420.5496 5303.1603)
      (11424.7023 5307.313) (11426.229 5312.9771) (11424.7023 5318.6412) (11420.5496 5322.7939) (11414.8855 5324.3053)
      (11409.2214 5322.7939) (11405.0687 5318.6412)
    ))
    ; P3377 -- see feature_dimensions_mm.csv
    ("06_ORNAMENT" 1 (
      (11403.5573 4717.5573) (11405.0687 4711.8931) (11409.2214 4707.7405) (11414.8855 4706.2137) (11420.5496 4707.7405)
      (11424.7023 4711.8931) (11426.229 4717.5573) (11424.7023 4723.2214) (11420.5496 4727.374) (11414.8855 4728.8855)
      (11409.2214 4727.374) (11405.0687 4723.2214)
    ))
    ; P3378 -- see feature_dimensions_mm.csv
    ("06_ORNAMENT" 1 (
      (11403.5573 4122.1374) (11405.0687 4116.4733) (11409.2214 4112.3206) (11414.8855 4110.7939) (11420.5496 4112.3206)
      (11424.7023 4116.4733) (11426.229 4122.1374) (11424.7023 4127.8015) (11420.5496 4131.9542) (11414.8855 4133.4656)
      (11409.2214 4131.9542) (11405.0687 4127.8015)
    ))
    ; P3379 -- see feature_dimensions_mm.csv
    ("06_ORNAMENT" 1 (
      (11423.6794 5211.7557) (11425.2061 5206.0916) (11429.3588 5201.9389) (11435.0229 5200.4275) (11440.687 5201.9389)
      (11444.8397 5206.0916) (11446.3511 5211.7557) (11444.8397 5217.4198) (11440.687 5221.5725) (11435.0229 5223.0992)
      (11429.3588 5221.5725) (11425.2061 5217.4198)
    ))
    ; P3380 -- see feature_dimensions_mm.csv
    ("06_ORNAMENT" 1 (
      (11423.6794 4818.7786) (11425.2061 4813.1145) (11429.3588 4808.9618) (11435.0229 4807.4351) (11440.687 4808.9618)
      (11444.8397 4813.1145) (11446.3511 4818.7786) (11444.8397 4824.4427) (11440.687 4828.5954) (11435.0229 4830.1069)
      (11429.3588 4828.5954) (11425.2061 4824.4427)
    ))
    ; P3381 -- see feature_dimensions_mm.csv
    ("06_ORNAMENT" 1 (
      (11423.6794 4616.3359) (11425.2061 4610.6718) (11429.3588 4606.5191) (11435.0229 4605.0076) (11440.687 4606.5191)
      (11444.8397 4610.6718) (11446.3511 4616.3359) (11444.8397 4622.0) (11440.687 4626.1527) (11435.0229 4627.6794)
      (11429.3588 4626.1527) (11425.2061 4622.0)
    ))
    ; P3382 -- see feature_dimensions_mm.csv
    ("06_ORNAMENT" 1 (
      (11423.6794 4223.3588) (11425.2061 4217.6947) (11429.3588 4213.542) (11435.0229 4212.0153) (11440.687 4213.542)
      (11444.8397 4217.6947) (11446.3511 4223.3588) (11444.8397 4229.0229) (11440.687 4233.1756) (11435.0229 4234.687)
      (11429.3588 4233.1756) (11425.2061 4229.0229)
    ))
    ; P3383 -- see feature_dimensions_mm.csv
    ("06_ORNAMENT" 1 (
      (11423.6794 4020.916) (11425.2061 4015.2519) (11429.3588 4011.0992) (11435.0229 4009.5878) (11440.687 4011.0992)
      (11444.8397 4015.2519) (11446.3511 4020.916) (11444.8397 4026.5802) (11440.687 4030.7328) (11435.0229 4032.2595)
      (11429.3588 4030.7328) (11425.2061 4026.5802)
    ))
    ; P3384 -- see feature_dimensions_mm.csv
    ("06_ORNAMENT" 1 (
      (11430.0 4122.1374) (11430.3664 4118.3969) (11431.4809 4114.7481) (11432.9618 4111.9084) (11433.4656 4100.626)
      (11436.2748 4079.2672) (11440.9313 4058.2443) (11447.4046 4037.7099) (11455.6489 4017.8015) (11465.5878 3998.7023)
      (11477.1603 3980.5344) (11490.2748 3963.4504) (11497.9084 3955.1298) (11498.855 3952.0611) (11500.6565 3948.7023)
      (11503.0382 3945.7863) (11505.9542 3943.4046) (11509.313 3941.6031) (11512.3817 3940.6565) (11520.7023 3933.0229)
      (11537.7863 3919.9084) (11555.9542 3908.3359) (11575.0534 3898.3969) (11594.9618 3890.1527) (11615.4962 3883.6794)
      (11636.5191 3879.0229) (11657.8779 3876.2137) (11669.1603 3875.7099) (11672.0 3874.229) (11675.6489 3873.1145)
      (11679.3893 3872.7481) (11683.1298 3873.1145) (11686.7786 3874.229) (11689.6183 3875.7099) (11700.9008 3876.2137)
      (11722.2595 3879.0229) (11743.2824 3883.6794) (11763.8168 3890.1527) (11783.7252 3898.3969) (11802.8244 3908.3359)
      (11820.9924 3919.9084) (11838.0763 3933.0229) (11846.3969 3940.6565) (11849.4656 3941.6031) (11852.8244 3943.4046)
      (11855.7405 3945.7863) (11858.1221 3948.7023) (11859.9237 3952.0611) (11860.8702 3955.1298) (11868.5038 3963.4504)
      (11881.6183 3980.5344) (11893.1908 3998.7023) (11903.1298 4017.8015) (11911.374 4037.7099) (11917.8473 4058.2443)
      (11922.5038 4079.2672) (11925.313 4100.626) (11925.8168 4111.9084) (11927.2977 4114.7481) (11928.4122 4118.3969)
      (11928.7786 4122.1374) (11928.4122 4125.8779) (11927.2977 4129.5267) (11925.8168 4132.3664) (11925.313 4143.6489)
      (11922.5038 4165.0076) (11917.8473 4186.0305) (11911.374 4206.5649) (11903.1298 4226.4733) (11893.1908 4245.5725)
      (11881.6183 4263.7405) (11868.5038 4280.8244) (11860.8702 4289.145) (11859.9237 4292.2137) (11858.1221 4295.5725)
      (11855.7405 4298.4885) (11852.8244 4300.8702) (11849.4656 4302.6718) (11846.3969 4303.6183) (11838.0763 4311.2519)
      (11820.9924 4324.3664) (11802.8244 4335.9389) (11783.7252 4345.8779) (11763.8168 4354.1221) (11743.2824 4360.5954)
      (11722.2595 4365.2519) (11700.9008 4368.0611) (11689.6183 4368.5649) (11686.7786 4370.0458) (11683.1298 4371.1603)
      (11679.3893 4371.5267) (11675.6489 4371.1603) (11672.0 4370.0458) (11669.1603 4368.5649) (11657.8779 4368.0611)
      (11636.5191 4365.2519) (11615.4962 4360.5954) (11594.9618 4354.1221) (11575.0534 4345.8779) (11555.9542 4335.9389)
      (11537.7863 4324.3664) (11520.7023 4311.2519) (11512.3817 4303.6183) (11509.313 4302.6718) (11505.9542 4300.8702)
      (11503.0382 4298.4885) (11500.6565 4295.5725) (11498.855 4292.2137) (11497.9084 4289.145) (11490.2748 4280.8244)
      (11477.1603 4263.7405) (11465.5878 4245.5725) (11455.6489 4226.4733) (11447.4046 4206.5649) (11440.9313 4186.0305)
      (11436.2748 4165.0076) (11433.4656 4143.6489) (11432.9618 4132.3664) (11431.4809 4129.5267) (11430.3664 4125.8779)
    ))
    ; P3385 -- see feature_dimensions_mm.csv
    ("06_ORNAMENT" 1 (
      (11431.2214 1861.9237) (11433.2214 1848.2595) (11437.8931 1836.458) (11445.145 1826.8244) (11454.7786 1819.5725)
      (11466.5802 1814.9008) (11480.2443 1812.9008) (11495.4198 1813.6489) (11511.771 1817.1145) (11528.855 1823.2061)
      (11546.2901 1831.771) (11563.6183 1842.626) (11580.4122 1855.4656) (11596.2748 1870.0) (11610.8092 1885.8626)
      (11623.6641 1902.6718) (11634.5038 1920.0) (11643.084 1937.4198) (11649.1756 1954.5191) (11652.6412 1970.855)
      (11653.374 1986.0458) (11651.3893 1999.7099) (11646.7176 2011.4962) (11639.4656 2021.145) (11629.8168 2028.3817)
      (11618.0305 2033.0687) (11604.3664 2035.0534) (11589.1756 2034.3053) (11572.8397 2030.855) (11555.7405 2024.7634)
      (11538.3206 2016.1832) (11520.9924 2005.3435) (11504.1832 1992.4885) (11488.3206 1977.9542) (11473.7863 1962.0916)
      (11460.9466 1945.2977) (11450.0916 1927.9695) (11441.5267 1910.5344) (11435.4351 1893.4504) (11431.9695 1877.0992)
    ))
    ; P3386 -- see feature_dimensions_mm.csv
    ("06_ORNAMENT" 1 (
      (11431.2214 1618.9924) (11431.9695 1603.8168) (11435.4351 1587.4656) (11441.5267 1570.3817) (11450.0916 1552.9466)
      (11460.9466 1535.6183) (11473.7863 1518.8244) (11488.3206 1502.9618) (11504.1832 1488.4275) (11520.9924 1475.5725)
      (11538.3206 1464.7328) (11555.7405 1456.1527) (11572.8397 1450.0611) (11589.1756 1446.5954) (11604.3664 1445.8626)
      (11618.0305 1447.8473) (11629.8168 1452.5191) (11639.4656 1459.771) (11646.7176 1469.4198) (11651.3893 1481.2061)
      (11653.374 1494.8702) (11652.6412 1510.0611) (11649.1756 1526.3969) (11643.084 1543.4962) (11634.5038 1560.916)
      (11623.6641 1578.2443) (11610.8092 1595.0534) (11596.2748 1610.916) (11580.4122 1625.4504) (11563.6183 1638.2901)
      (11546.2901 1649.145) (11528.855 1657.7099) (11511.771 1663.8015) (11495.4198 1667.2672) (11480.2443 1668.0153)
      (11466.5802 1666.0153) (11454.7786 1661.3435) (11445.145 1654.0916) (11437.8931 1644.458) (11433.2214 1632.6565)
    ))
    ; P3387 -- see feature_dimensions_mm.csv
    ("06_ORNAMENT" 1 (
      (11458.7023 5232.0) (11459.9389 5224.2137) (11463.5115 5217.1908) (11469.084 5211.6183) (11476.1069 5208.0458)
      (11483.8931 5206.8092) (11491.6794 5208.0458) (11498.7023 5211.6183) (11504.2748 5217.1908) (11507.8473 5224.2137)
      (11509.084 5232.0) (11507.8473 5239.7863) (11504.2748 5246.8092) (11498.7023 5252.3817) (11491.6794 5255.9542)
      (11483.8931 5257.1908) (11476.1069 5255.9542) (11469.084 5252.3817) (11463.5115 5246.8092) (11459.9389 5239.7863)
    ))
    ; P3388 -- see feature_dimensions_mm.csv
    ("06_ORNAMENT" 1 (
      (11458.7023 4798.5344) (11459.9389 4790.7481) (11463.5115 4783.7252) (11469.084 4778.1527) (11476.1069 4774.5802)
      (11483.8931 4773.3435) (11491.6794 4774.5802) (11498.7023 4778.1527) (11504.2748 4783.7252) (11507.8473 4790.7481)
      (11509.084 4798.5344) (11507.8473 4806.3206) (11504.2748 4813.3435) (11498.7023 4818.916) (11491.6794 4822.4885)
      (11483.8931 4823.7252) (11476.1069 4822.4885) (11469.084 4818.916) (11463.5115 4813.3435) (11459.9389 4806.3206)
    ))
    ; P3389 -- see feature_dimensions_mm.csv
    ("06_ORNAMENT" 1 (
      (11458.7023 4636.5802) (11459.9389 4628.7939) (11463.5115 4621.771) (11469.084 4616.1985) (11476.1069 4612.626)
      (11483.8931 4611.3893) (11491.6794 4612.626) (11498.7023 4616.1985) (11504.2748 4621.771) (11507.8473 4628.7939)
      (11509.084 4636.5802) (11507.8473 4644.3664) (11504.2748 4651.3893) (11498.7023 4656.9618) (11491.6794 4660.5344)
      (11483.8931 4661.771) (11476.1069 4660.5344) (11469.084 4656.9618) (11463.5115 4651.3893) (11459.9389 4644.3664)
    ))
    ; P3390 -- see feature_dimensions_mm.csv
    ("06_ORNAMENT" 1 (
      (11458.7023 4203.1145) (11459.9389 4195.3282) (11463.5115 4188.3053) (11469.084 4182.7328) (11476.1069 4179.1603)
      (11483.8931 4177.9237) (11491.6794 4179.1603) (11498.7023 4182.7328) (11504.2748 4188.3053) (11507.8473 4195.3282)
      (11509.084 4203.1145) (11507.8473 4210.9008) (11504.2748 4217.9237) (11498.7023 4223.4962) (11491.6794 4227.0687)
      (11483.8931 4228.3053) (11476.1069 4227.0687) (11469.084 4223.4962) (11463.5115 4217.9237) (11459.9389 4210.9008)
    ))
    ; P3391 -- see feature_dimensions_mm.csv
    ("06_ORNAMENT" 1 (
      (11458.7023 4041.1603) (11459.9389 4033.374) (11463.5115 4026.3511) (11469.084 4020.7786) (11476.1069 4017.2061)
      (11483.8931 4015.9695) (11491.6794 4017.2061) (11498.7023 4020.7786) (11504.2748 4026.3511) (11507.8473 4033.374)
      (11509.084 4041.1603) (11507.8473 4048.9466) (11504.2748 4055.9695) (11498.7023 4061.542) (11491.6794 4065.1145)
      (11483.8931 4066.3511) (11476.1069 4065.1145) (11469.084 4061.542) (11463.5115 4055.9695) (11459.9389 4048.9466)
    ))
    ; P3392 -- see feature_dimensions_mm.csv
    ("06_ORNAMENT" 1 (
      (11459.4809 2099.7557) (11460.8244 2088.3664) (11463.6031 2077.9542) (11467.7557 2068.7786) (11473.1908 2061.0687)
      (11479.771 2055.0076) (11487.313 2050.7634) (11495.6489 2048.4275) (11504.5802 2048.0611) (11513.8626 2049.6794)
      (11523.2977 2053.2214) (11532.626 2058.6107) (11541.6336 2065.7252) (11550.1069 2074.3817) (11557.8168 2084.3664)
      (11564.5802 2095.4351) (11570.229 2107.313) (11574.626 2119.7099) (11575.8931 2124.9618) (11579.6794 2124.2901)
      (11585.0229 2123.6031) (11588.8397 2122.8702) (11590.8244 2121.5267) (11590.9924 2119.145) (11589.7252 2115.4656)
      (11587.6489 2110.5038) (11585.4962 2104.5802) (11584.0153 2098.2901) (11583.7557 2092.3664) (11585.0076 2087.5573)
      (11587.7863 2084.5191) (11591.8015 2083.6336) (11596.5954 2084.9466) (11601.6031 2088.1374) (11606.3053 2092.5802)
      (11610.3664 2097.3893) (11613.6183 2101.6641) (11616.1679 2104.6107) (11618.3206 2105.6489) (11620.4733 2104.6107)
      (11623.0229 2101.6641) (11626.2748 2097.3893) (11630.3359 2092.5802) (11635.0382 2088.1374) (11640.0458 2084.9466)
      (11644.8397 2083.6336) (11648.855 2084.5191) (11651.6336 2087.5573) (11652.8855 2092.3664) (11652.626 2098.2901)
      (11651.145 2104.5802) (11648.9924 2110.5038) (11646.916 2115.4656) (11645.6489 2119.145) (11645.8168 2121.5267)
      (11647.8015 2122.8702) (11651.6183 2123.6031) (11656.9618 2124.2901) (11663.145 2125.3893) (11669.3435 2127.2519)
      (11674.6107 2130.0) (11678.1527 2133.4809) (11679.3893 2137.4046) (11678.1527 2141.3282) (11674.6107 2144.8092)
      (11669.3435 2147.5573) (11663.145 2149.4198) (11656.9618 2150.5191) (11651.6183 2151.2061) (11647.8015 2151.9389)
      (11645.8168 2153.2824) (11645.6489 2155.6641) (11646.916 2159.3435) (11648.9924 2164.3053) (11651.145 2170.229)
      (11652.1679 2174.5954) (11637.6031 2185.8473) (11635.7252 2187.0992) (11635.0382 2186.6718) (11630.3359 2182.229)
      (11626.2748 2177.4198) (11623.0229 2173.145) (11620.4733 2170.1985) (11618.3206 2169.1603) (11616.1679 2170.1985)
      (11613.6183 2173.145) (11610.3664 2177.4198) (11606.3053 2182.229) (11601.6031 2186.6718) (11596.5954 2189.8626)
      (11591.8015 2191.1756) (11587.7863 2190.2901) (11585.0076 2187.2519) (11583.7557 2182.4427) (11584.0153 2176.5191)
      (11585.4962 2170.229) (11587.6489 2164.3053) (11589.7252 2159.3435) (11590.9924 2155.6641) (11590.8244 2153.2824)
      (11588.8397 2151.9389) (11585.0229 2151.2061) (11579.6794 2150.5191) (11579.3435 2150.458) (11579.4198 2156.9313)
      (11578.0763 2168.3359) (11575.2977 2178.7481) (11571.1298 2187.9237) (11565.6947 2195.6336) (11559.1298 2201.6794)
      (11551.5878 2205.9237) (11543.2366 2208.2595) (11534.3206 2208.626) (11525.0229 2207.0229) (11515.6031 2203.4656)
      (11506.2595 2198.0763) (11497.2519 2190.9618) (11488.7939 2182.3053) (11481.084 2172.3206) (11474.3206 2161.2519)
      (11468.6718 2149.374) (11464.2748 2136.9771) (11461.2214 2124.3817) (11459.6183 2111.8626)
    ))
    ; P3393 -- see feature_dimensions_mm.csv
    ("06_ORNAMENT" 1 (
      (11459.4809 1381.145) (11459.6183 1369.0534) (11461.2214 1356.5344) (11464.2748 1343.9389) (11468.6718 1331.542)
      (11474.3206 1319.6641) (11481.084 1308.5954) (11488.7939 1298.6107) (11497.2519 1289.9542) (11506.2595 1282.8397)
      (11515.6031 1277.4504) (11525.0229 1273.8931) (11534.3206 1272.2901) (11543.2366 1272.6565) (11551.5878 1274.9924)
      (11559.1298 1279.2366) (11565.6947 1285.2824) (11571.1298 1292.9924) (11575.2977 1302.1679) (11578.0763 1312.5802)
      (11579.4198 1323.9847) (11579.2824 1336.0916) (11577.6641 1348.5954) (11574.626 1361.2061) (11574.3969 1361.8779)
      (11579.6794 1360.9313) (11585.0229 1360.2443) (11588.8397 1359.5115) (11590.8244 1358.1679) (11590.9924 1355.7863)
      (11589.7252 1352.1069) (11587.6489 1347.145) (11585.4962 1341.2214) (11584.0153 1334.9313) (11583.7557 1329.0076)
      (11585.0076 1324.1985) (11587.7863 1321.1603) (11591.8015 1320.2748) (11596.5954 1321.5878) (11601.6031 1324.7786)
      (11606.3053 1329.2214) (11610.3664 1334.0305) (11613.6183 1338.3053) (11616.1679 1341.2519) (11618.3206 1342.2901)
      (11620.4733 1341.2519) (11623.0229 1338.3053) (11626.2748 1334.0305) (11630.3359 1329.2214) (11635.0382 1324.7786)
      (11640.0458 1321.5878) (11644.8397 1320.2748) (11648.855 1321.1603) (11651.6336 1324.1985) (11652.8855 1329.0076)
      (11652.626 1334.9313) (11651.145 1341.2214) (11648.9924 1347.145) (11646.916 1352.1069) (11645.6489 1355.7863)
      (11645.8168 1358.1679) (11647.8015 1359.5115) (11651.6183 1360.2443) (11656.9618 1360.9313) (11663.145 1362.0305)
      (11669.3435 1363.8931) (11674.6107 1366.6412) (11678.1527 1370.1221) (11679.3893 1374.0458) (11678.1527 1377.9695)
      (11676.7328 1379.3588) (11682.6412 1378.4275) (11694.4427 1380.2901) (11705.084 1385.7099) (11713.5267 1394.1527)
      (11718.9466 1404.7939) (11720.8092 1416.5954) (11718.9466 1428.3817) (11713.5267 1439.0229) (11705.084 1447.4656)
      (11694.4427 1452.8855) (11682.6412 1454.7634) (11670.855 1452.8855) (11660.2137 1447.4656) (11651.771 1439.0229)
      (11646.3511 1428.3817) (11646.2137 1427.5115) (11644.8397 1427.8168) (11640.0458 1426.5038) (11635.0382 1423.313)
      (11630.3359 1418.8702) (11626.2748 1414.0611) (11623.0229 1409.7863) (11620.4733 1406.8397) (11618.3206 1405.8015)
      (11616.1679 1406.8397) (11613.6183 1409.7863) (11610.3664 1414.0611) (11606.3053 1418.8702) (11601.6031 1423.313)
      (11596.5954 1426.5038) (11591.8015 1427.8168) (11587.7863 1426.9313) (11585.0076 1423.8931) (11583.7557 1419.084)
      (11584.0153 1413.1603) (11585.4962 1406.8702) (11587.6489 1400.9466) (11589.7252 1395.9847) (11590.9924 1392.3053)
      (11590.8244 1389.9237) (11588.8397 1388.5802) (11585.0229 1387.8473) (11579.6794 1387.1603) (11573.4962 1386.0611)
      (11567.2977 1384.1985) (11565.6031 1383.313) (11564.5802 1385.4809) (11557.8168 1396.5496) (11550.1069 1406.5344)
      (11541.6336 1415.1908) (11532.626 1422.3053) (11523.2977 1427.6947) (11513.8626 1431.2366) (11504.5802 1432.855)
      (11495.6489 1432.4885) (11487.313 1430.1527) (11479.771 1425.9084) (11473.1908 1419.8473) (11467.7557 1412.1374)
      (11463.6031 1402.9618) (11460.8244 1392.5496)
    ))
    ; P3394 -- see feature_dimensions_mm.csv
    ("06_ORNAMENT" 1 (
      (11480.916 1740.458) (11482.6107 1728.5191) (11487.6336 1716.8702) (11495.8931 1705.8015) (11507.1603 1695.5878)
      (11521.1603 1686.4733) (11537.5573 1678.7023) (11555.9389 1672.4427) (11575.8626 1667.8626) (11596.8244 1665.0687)
      (11618.3206 1664.1221) (11639.8168 1665.0687) (11660.7786 1667.8626) (11680.7023 1672.4427) (11699.084 1678.7023)
      (11715.4809 1686.4733) (11729.4809 1695.5878) (11740.7481 1705.8015) (11749.0076 1716.8702) (11754.0305 1728.5191)
      (11755.7252 1740.458) (11754.0305 1752.3969) (11749.0076 1764.0458) (11740.7481 1775.1145) (11729.4809 1785.3282)
      (11715.4809 1794.4427) (11699.084 1802.2137) (11680.7023 1808.4733) (11660.7786 1813.0534) (11639.8168 1815.8473)
      (11618.3206 1816.7939) (11596.8244 1815.8473) (11575.8626 1813.0534) (11555.9389 1808.4733) (11537.5573 1802.2137)
      (11521.1603 1794.4427) (11507.1603 1785.3282) (11495.8931 1775.1145) (11487.6336 1764.0458) (11482.6107 1752.3969)
    ))
    ; P3395 -- see feature_dimensions_mm.csv
    ("06_ORNAMENT" 1 (
      (11481.0229 5125.9389) (11482.5344 5120.2748) (11486.687 5116.1221) (11492.3511 5114.6107) (11498.0305 5116.1221)
      (11502.1679 5120.2748) (11503.6947 5125.9389) (11502.1679 5131.6183) (11498.0305 5135.7557) (11492.3511 5137.2824)
      (11486.687 5135.7557) (11482.5344 5131.6183)
    ))
    ; P3396 -- see feature_dimensions_mm.csv
    ("06_ORNAMENT" 1 (
      (11481.0229 4904.5954) (11482.5344 4898.916) (11486.687 4894.7786) (11492.3511 4893.2519) (11498.0305 4894.7786)
      (11502.1679 4898.916) (11503.6947 4904.5954) (11502.1679 4910.2595) (11498.0305 4914.4122) (11492.3511 4915.9237)
      (11486.687 4914.4122) (11482.5344 4910.2595)
    ))
    ; P3397 -- see feature_dimensions_mm.csv
    ("06_ORNAMENT" 1 (
      (11481.0229 4530.5191) (11482.5344 4524.855) (11486.687 4520.7023) (11492.3511 4519.1908) (11498.0305 4520.7023)
      (11502.1679 4524.855) (11503.6947 4530.5191) (11502.1679 4536.1985) (11498.0305 4540.3359) (11492.3511 4541.8626)
      (11486.687 4540.3359) (11482.5344 4536.1985)
    ))
    ; P3398 -- see feature_dimensions_mm.csv
    ("06_ORNAMENT" 1 (
      (11481.0229 4309.1756) (11482.5344 4303.4962) (11486.687 4299.3588) (11492.3511 4297.8321) (11498.0305 4299.3588)
      (11502.1679 4303.4962) (11503.6947 4309.1756) (11502.1679 4314.8397) (11498.0305 4318.9924) (11492.3511 4320.5038)
      (11486.687 4318.9924) (11482.5344 4314.8397)
    ))
    ; P3399 -- see feature_dimensions_mm.csv
    ("06_ORNAMENT" 1 (
      (11481.0229 3935.0992) (11482.5344 3929.4351) (11486.687 3925.2824) (11492.3511 3923.771) (11498.0305 3925.2824)
      (11502.1679 3929.4351) (11503.6947 3935.0992) (11502.1679 3940.7786) (11498.0305 3944.916) (11492.3511 3946.4427)
      (11486.687 3944.916) (11482.5344 3940.7786)
    ))
    ; P3400 -- see feature_dimensions_mm.csv
    ("06_ORNAMENT" 1 (
      (11490.458 5312.9771) (11491.1756 5307.8473) (11493.2977 5302.855) (11496.7786 5298.1069) (11501.5267 5293.7252)
      (11507.4351 5289.8168) (11514.3359 5286.4885) (11522.0916 5283.8015) (11530.4885 5281.8321) (11539.3282 5280.626)
      (11548.3969 5280.229) (11557.4656 5280.626) (11566.3053 5281.8321) (11574.7023 5283.8015) (11582.458 5286.4885)
      (11589.3588 5289.8168) (11595.2672 5293.7252) (11600.0153 5298.1069) (11603.4962 5302.855) (11605.6183 5307.8473)
      (11606.3359 5312.9771) (11605.6183 5318.1069) (11603.4962 5323.0992) (11600.0153 5327.8473) (11595.2672 5332.229)
      (11589.3588 5336.1374) (11582.458 5339.4656) (11574.7023 5342.1527) (11566.3053 5344.1221) (11557.4656 5345.3282)
      (11548.3969 5345.7252) (11539.3282 5345.3282) (11530.4885 5344.1221) (11522.0916 5342.1527) (11514.3359 5339.4656)
      (11507.4351 5336.1374) (11501.5267 5332.229) (11496.7786 5327.8473) (11493.2977 5323.0992) (11491.1756 5318.1069)
    ))
    ; P3401 -- see feature_dimensions_mm.csv
    ("06_ORNAMENT" 1 (
      (11490.458 4717.5573) (11491.1756 4712.4275) (11493.2977 4707.4351) (11496.7786 4702.687) (11501.5267 4698.3053)
      (11507.4351 4694.3969) (11514.3359 4691.0687) (11522.0916 4688.3817) (11530.4885 4686.4122) (11539.3282 4685.2061)
      (11548.3969 4684.8092) (11557.4656 4685.2061) (11566.3053 4686.4122) (11574.7023 4688.3817) (11582.458 4691.0687)
      (11589.3588 4694.3969) (11595.2672 4698.3053) (11600.0153 4702.687) (11603.4962 4707.4351) (11605.6183 4712.4275)
      (11606.3359 4717.5573) (11605.6183 4722.687) (11603.4962 4727.6794) (11600.0153 4732.4275) (11595.2672 4736.8092)
      (11589.3588 4740.7176) (11582.458 4744.0458) (11574.7023 4746.7328) (11566.3053 4748.7023) (11557.4656 4749.9084)
      (11548.3969 4750.3053) (11539.3282 4749.9084) (11530.4885 4748.7023) (11522.0916 4746.7328) (11514.3359 4744.0458)
      (11507.4351 4740.7176) (11501.5267 4736.8092) (11496.7786 4732.4275) (11493.2977 4727.6794) (11491.1756 4722.687)
    ))
    ; P3402 -- see feature_dimensions_mm.csv
    ("06_ORNAMENT" 1 (
      (11490.458 4122.1374) (11491.1756 4117.0076) (11493.2977 4112.0153) (11496.7786 4107.2672) (11501.5267 4102.8855)
      (11507.4351 4098.9771) (11514.3359 4095.6489) (11522.0916 4092.9618) (11530.4885 4090.9924) (11539.3282 4089.7863)
      (11548.3969 4089.3893) (11557.4656 4089.7863) (11566.3053 4090.9924) (11574.7023 4092.9618) (11582.458 4095.6489)
      (11589.3588 4098.9771) (11595.2672 4102.8855) (11600.0153 4107.2672) (11603.4962 4112.0153) (11605.6183 4117.0076)
      (11606.3359 4122.1374) (11605.6183 4127.2672) (11603.4962 4132.2595) (11600.0153 4137.0076) (11595.2672 4141.3893)
      (11589.3588 4145.2977) (11582.458 4148.626) (11574.7023 4151.313) (11566.3053 4153.2824) (11557.4656 4154.4885)
      (11548.3969 4154.8855) (11539.3282 4154.4885) (11530.4885 4153.2824) (11522.0916 4151.313) (11514.3359 4148.626)
      (11507.4351 4145.2977) (11501.5267 4141.3893) (11496.7786 4137.0076) (11493.2977 4132.2595) (11491.1756 4127.2672)
    ))
    ; P3403 -- see feature_dimensions_mm.csv
    ("06_ORNAMENT" 1 (
      (11502.2901 5022.9008) (11502.7023 5020.3206) (11503.8931 5017.8931) (11505.7863 5015.6947) (11508.2443 5013.8626)
      (11511.084 5012.4122) (11514.1069 5011.3588) (11517.145 5010.6412) (11519.9847 5010.1985) (11522.5038 5009.8779)
      (11524.5954 5009.5573) (11526.229 5009.084) (11527.3893 5008.3053) (11528.1679 5007.145) (11528.6412 5005.5115)
      (11528.9618 5003.4198) (11529.2824 5000.9008) (11529.7252 4998.0611) (11530.4427 4995.0229) (11531.4962 4992.0)
      (11532.9466 4989.1603) (11534.7786 4986.7023) (11536.9771 4984.8092) (11539.4046 4983.6183) (11541.9847 4983.2061)
      (11544.5649 4983.6183) (11546.9924 4984.8092) (11549.1908 4986.7023) (11551.0229 4989.1603) (11552.4733 4992.0)
      (11553.5267 4995.0229) (11554.2443 4998.0611) (11554.687 5000.9008) (11555.0076 5003.4198) (11555.3282 5005.5115)
      (11555.8015 5007.145) (11556.5802 5008.3053) (11557.7405 5009.084) (11559.374 5009.5573) (11561.4656 5009.8779)
      (11563.9847 5010.1985) (11566.8244 5010.6412) (11569.8626 5011.3588) (11572.8855 5012.4122) (11575.7252 5013.8626)
      (11578.1832 5015.6947) (11580.0763 5017.8931) (11581.2672 5020.3206) (11581.6794 5022.9008) (11581.2672 5025.4809)
      (11580.0763 5027.9084) (11578.1832 5030.1069) (11575.7252 5031.9389) (11572.8855 5033.3893) (11569.8626 5034.4427)
      (11566.8244 5035.1603) (11563.9847 5035.6031) (11561.4656 5035.9237) (11559.374 5036.2443) (11557.7405 5036.7176)
      (11556.5802 5037.4962) (11555.8015 5038.6565) (11555.3282 5040.2901) (11555.0076 5042.3817) (11554.687 5044.9008)
      (11554.2443 5047.7405) (11553.5267 5050.7786) (11552.4733 5053.8015) (11551.0229 5056.6412) (11549.1908 5059.0992)
      (11546.9924 5060.9924) (11544.5649 5062.1832) (11541.9847 5062.5954) (11539.4046 5062.1832) (11536.9771 5060.9924)
      (11534.7786 5059.0992) (11532.9466 5056.6412) (11531.4962 5053.8015) (11530.4427 5050.7786) (11529.7252 5047.7405)
      (11529.2824 5044.9008) (11528.9618 5042.3817) (11528.6412 5040.2901) (11528.1679 5038.6565) (11527.3893 5037.4962)
      (11526.229 5036.7176) (11524.5954 5036.2443) (11522.5038 5035.9237) (11519.9847 5035.6031) (11517.145 5035.1603)
      (11514.1069 5034.4427) (11511.084 5033.3893) (11508.2443 5031.9389) (11505.7863 5030.1069) (11503.8931 5027.9084)
      (11502.7023 5025.4809)
    ))
    ; P3404 -- see feature_dimensions_mm.csv
    ("06_ORNAMENT" 1 (
      (11539.7405 5194.3664) (11540.6412 5188.5496) (11542.6718 5183.5115) (11545.8015 5179.3893) (11549.9237 5176.2595)
      (11554.9618 5174.229) (11560.7786 5173.3282) (11567.2366 5173.6031) (11574.1679 5175.0076) (11581.4198 5177.542)
      (11588.7939 5181.1145) (11596.1221 5185.6641) (11603.2214 5191.0687) (11609.9237 5197.1908) (11616.0458 5203.8931)
      (11621.4504 5210.9924) (11626.0 5218.3206) (11629.5725 5225.6947) (11632.1069 5232.9466) (11633.5267 5239.8779)
      (11633.7863 5246.3359) (11632.8855 5252.1527) (11630.855 5257.1908) (11627.7252 5261.313) (11623.6031 5264.4427)
      (11618.5649 5266.4733) (11612.7481 5267.374) (11606.2901 5267.1145) (11599.3588 5265.6947) (11592.1069 5263.1603)
      (11584.7328 5259.5878) (11577.4046 5255.0382) (11570.3053 5249.6336) (11563.6031 5243.5115) (11557.4809 5236.8092)
      (11552.0763 5229.7099) (11547.5267 5222.3817) (11543.9542 5215.0076) (11541.4198 5207.7557) (11540.0153 5200.8244)
    ))
    ; P3405 -- see feature_dimensions_mm.csv
    ("06_ORNAMENT" 1 (
      (11539.7405 4836.1679) (11540.0153 4829.7099) (11541.4198 4822.7786) (11543.9542 4815.5267) (11547.5267 4808.1527)
      (11552.0763 4800.8244) (11557.4809 4793.7252) (11563.6031 4787.0229) (11570.3053 4780.9008) (11577.4046 4775.4962)
      (11584.7328 4770.9466) (11592.1069 4767.374) (11599.3588 4764.8397) (11606.2901 4763.4198) (11612.7481 4763.1603)
      (11618.5649 4764.0611) (11623.6031 4766.0916) (11627.7252 4769.2214) (11630.855 4773.3435) (11632.8855 4778.3817)
      (11633.7863 4784.1985) (11633.5267 4790.6565) (11632.1069 4797.5878) (11629.5725 4804.8397) (11626.0 4812.2137)
      (11621.4504 4819.542) (11616.0458 4826.6412) (11609.9237 4833.3435) (11603.2214 4839.4656) (11596.1221 4844.8702)
      (11588.7939 4849.4198) (11581.4198 4852.9924) (11574.1679 4855.5267) (11567.2366 4856.9313) (11560.7786 4857.2061)
      (11554.9618 4856.3053) (11549.9237 4854.2748) (11545.8015 4851.145) (11542.6718 4847.0229) (11540.6412 4841.9847)
    ))
    ; P3406 -- see feature_dimensions_mm.csv
    ("06_ORNAMENT" 1 (
      (11539.7405 4598.9466) (11540.6412 4593.1298) (11542.6718 4588.0916) (11545.8015 4583.9695) (11549.9237 4580.8397)
      (11554.9618 4578.8092) (11560.7786 4577.9084) (11567.2366 4578.1832) (11574.1679 4579.5878) (11581.4198 4582.1221)
      (11588.7939 4585.6947) (11596.1221 4590.2443) (11603.2214 4595.6489) (11609.9237 4601.771) (11616.0458 4608.4733)
      (11621.4504 4615.5725) (11626.0 4622.9008) (11629.5725 4630.2748) (11632.1069 4637.5267) (11633.5267 4644.458)
      (11633.7863 4650.916) (11632.8855 4656.7328) (11630.855 4661.771) (11627.7252 4665.8931) (11623.6031 4669.0229)
      (11618.5649 4671.0534) (11612.7481 4671.9542) (11606.2901 4671.6947) (11599.3588 4670.2748) (11592.1069 4667.7405)
      (11584.7328 4664.1679) (11577.4046 4659.6183) (11570.3053 4654.2137) (11563.6031 4648.0916) (11557.4809 4641.3893)
      (11552.0763 4634.2901) (11547.5267 4626.9618) (11543.9542 4619.5878) (11541.4198 4612.3359) (11540.0153 4605.4046)
    ))
    ; P3407 -- see feature_dimensions_mm.csv
    ("06_ORNAMENT" 1 (
      (11539.7405 4240.7481) (11540.0153 4234.2901) (11541.4198 4227.3588) (11543.9542 4220.1069) (11547.5267 4212.7328)
      (11552.0763 4205.4046) (11557.4809 4198.3053) (11563.6031 4191.6031) (11570.3053 4185.4809) (11577.4046 4180.0763)
      (11584.7328 4175.5267) (11592.1069 4171.9542) (11599.3588 4169.4198) (11606.2901 4168.0) (11612.7481 4167.7405)
      (11618.5649 4168.6412) (11623.6031 4170.6718) (11627.7252 4173.8015) (11630.855 4177.9237) (11632.8855 4182.9618)
      (11633.7863 4188.7786) (11633.5267 4195.2366) (11632.1069 4202.1679) (11629.5725 4209.4198) (11626.0 4216.7939)
      (11621.4504 4224.1221) (11616.0458 4231.2214) (11609.9237 4237.9237) (11603.2214 4244.0458) (11596.1221 4249.4504)
      (11588.7939 4254.0) (11581.4198 4257.5725) (11574.1679 4260.1069) (11567.2366 4261.5115) (11560.7786 4261.7863)
      (11554.9618 4260.8855) (11549.9237 4258.855) (11545.8015 4255.7252) (11542.6718 4251.6031) (11540.6412 4246.5649)
    ))
    ; P3408 -- see feature_dimensions_mm.csv
    ("06_ORNAMENT" 1 (
      (11539.7405 4003.5267) (11540.6412 3997.7099) (11542.6718 3992.6718) (11545.8015 3988.5496) (11549.9237 3985.4198)
      (11554.9618 3983.3893) (11560.7786 3982.4885) (11567.2366 3982.7634) (11574.1679 3984.1679) (11581.4198 3986.7023)
      (11588.7939 3990.2748) (11596.1221 3994.8244) (11603.2214 4000.229) (11609.9237 4006.3511) (11616.0458 4013.0534)
      (11621.4504 4020.1527) (11626.0 4027.4809) (11629.5725 4034.855) (11632.1069 4042.1069) (11633.5267 4049.0382)
      (11633.7863 4055.4962) (11632.8855 4061.313) (11630.855 4066.3511) (11627.7252 4070.4733) (11623.6031 4073.6031)
      (11618.5649 4075.6336) (11612.7481 4076.5344) (11606.2901 4076.2748) (11599.3588 4074.855) (11592.1069 4072.3206)
      (11584.7328 4068.7481) (11577.4046 4064.1985) (11570.3053 4058.7939) (11563.6031 4052.6718) (11557.4809 4045.9695)
      (11552.0763 4038.8702) (11547.5267 4031.542) (11543.9542 4024.1679) (11541.4198 4016.916) (11540.0153 4009.9847)
    ))
    ; P3409 -- see feature_dimensions_mm.csv
    ("06_ORNAMENT" 1 (
      (11548.0916 7374.0458) (11549.4504 7371.5267) (11553.1603 7369.4809) (11558.1985 7368.1527) (11563.2519 7367.4656)
      (11567.0382 7367.0076) (11568.7176 7366.1527) (11568.1221 7364.3511) (11565.7863 7361.3435) (11562.7023 7357.2824)
      (11560.0763 7352.7786) (11558.9008 7348.7176) (11559.7252 7345.9847) (11562.458 7345.1603) (11566.5191 7346.3359)
      (11571.0229 7348.9618) (11575.084 7352.0458) (11578.0916 7354.3817) (11579.8931 7354.9771) (11580.7481 7353.2977)
      (11581.2061 7349.5115) (11581.9084 7344.458) (11583.2214 7339.4198) (11585.2672 7335.7099) (11587.7863 7334.3511)
      (11590.3053 7335.7099) (11592.3511 7339.4198) (11593.6794 7344.458) (11594.3664 7349.5115) (11594.8244 7353.2977)
      (11595.6794 7354.9771) (11597.4809 7354.3817) (11600.4885 7352.0458) (11604.5496 7348.9618) (11609.0534 7346.3359)
      (11613.1145 7345.1603) (11615.8473 7345.9847) (11616.6718 7348.7176) (11615.4962 7352.7786) (11612.8702 7357.2824)
      (11609.7863 7361.3435) (11607.4504 7364.3511) (11606.855 7366.1527) (11608.5344 7367.0076) (11612.3206 7367.4656)
      (11617.374 7368.1527) (11622.4122 7369.4809) (11626.1221 7371.5267) (11627.4809 7374.0458) (11626.1221 7376.5649)
      (11622.4122 7378.6107) (11617.374 7379.9237) (11612.3206 7380.626) (11608.5344 7381.084) (11606.855 7381.9389)
      (11607.4504 7383.7405) (11609.7863 7386.7481) (11612.8702 7390.8092) (11615.4962 7395.313) (11616.6718 7399.374)
      (11615.8473 7402.1069) (11613.1145 7402.9313) (11609.0534 7401.7557) (11604.5496 7399.1298) (11600.4885 7396.0458)
      (11597.4809 7393.7099) (11595.6794 7393.1145) (11594.8244 7394.7939) (11594.3664 7398.5802) (11593.6794 7403.6336)
      (11592.3511 7408.6718) (11590.3053 7412.3817) (11587.7863 7413.7405) (11585.2672 7412.3817) (11583.2214 7408.6718)
      (11581.9084 7403.6336) (11581.2061 7398.5802) (11580.7481 7394.7939) (11579.8931 7393.1145) (11578.0916 7393.7099)
      (11575.084 7396.0458) (11571.0229 7399.1298) (11566.5191 7401.7557) (11562.458 7402.9313) (11559.7252 7402.1069)
      (11558.9008 7399.374) (11560.0763 7395.313) (11562.7023 7390.8092) (11565.7863 7386.7481) (11568.1221 7383.7405)
      (11568.7176 7381.9389) (11567.0382 7381.084) (11563.2519 7380.626) (11558.1985 7379.9237) (11553.1603 7378.6107)
      (11549.4504 7376.5649)
    ))
    ; P3410 -- see feature_dimensions_mm.csv
    ("06_ORNAMENT" 1 (
      (11548.0916 7206.1069) (11549.4504 7203.5878) (11553.1603 7201.542) (11558.1985 7200.2137) (11563.2519 7199.5267)
      (11567.0382 7199.0687) (11568.7176 7198.2137) (11568.1221 7196.4122) (11565.7863 7193.4046) (11562.7023 7189.3435)
      (11560.0763 7184.8397) (11558.9008 7180.7786) (11559.7252 7178.0458) (11562.458 7177.2214) (11566.5191 7178.3969)
      (11571.0229 7181.0229) (11575.084 7184.1069) (11578.0916 7186.4427) (11579.8931 7187.0382) (11580.7481 7185.3588)
      (11581.2061 7181.5725) (11581.9084 7176.5191) (11583.2214 7171.4809) (11585.2672 7167.771) (11587.7863 7166.4122)
      (11590.3053 7167.771) (11592.3511 7171.4809) (11593.6794 7176.5191) (11594.3664 7181.5725) (11594.8244 7185.3588)
      (11595.6794 7187.0382) (11597.4809 7186.4427) (11600.4885 7184.1069) (11604.5496 7181.0229) (11609.0534 7178.3969)
      (11613.1145 7177.2214) (11615.8473 7178.0458) (11616.6718 7180.7786) (11615.4962 7184.8397) (11612.8702 7189.3435)
      (11609.7863 7193.4046) (11607.4504 7196.4122) (11606.855 7198.2137) (11608.5344 7199.0687) (11612.3206 7199.5267)
      (11617.374 7200.2137) (11622.4122 7201.542) (11626.1221 7203.5878) (11627.4809 7206.1069) (11626.1221 7208.626)
      (11622.4122 7210.6718) (11617.374 7211.9847) (11612.3206 7212.687) (11608.5344 7213.145) (11606.855 7214.0)
      (11607.4504 7215.8015) (11609.7863 7218.8092) (11612.8702 7222.8702) (11615.4962 7227.374) (11616.6718 7231.4351)
      (11615.8473 7234.1679) (11613.1145 7234.9924) (11609.0534 7233.8168) (11604.5496 7231.1908) (11600.4885 7228.1069)
      (11597.4809 7225.771) (11595.6794 7225.1756) (11594.8244 7226.855) (11594.3664 7230.6412) (11593.6794 7235.6947)
      (11592.3511 7240.7328) (11590.3053 7244.4427) (11587.7863 7245.8015) (11585.2672 7244.4427) (11583.2214 7240.7328)
      (11581.9084 7235.6947) (11581.2061 7230.6412) (11580.7481 7226.855) (11579.8931 7225.1756) (11578.0916 7225.771)
      (11575.084 7228.1069) (11571.0229 7231.1908) (11566.5191 7233.8168) (11562.458 7234.9924) (11559.7252 7234.1679)
      (11558.9008 7231.4351) (11560.0763 7227.374) (11562.7023 7222.8702) (11565.7863 7218.8092) (11568.1221 7215.8015)
      (11568.7176 7214.0) (11567.0382 7213.145) (11563.2519 7212.687) (11558.1985 7211.9847) (11553.1603 7210.6718)
      (11549.4504 7208.626)
    ))
    ; P3411 -- see feature_dimensions_mm.csv
    ("06_ORNAMENT" 1 (
      (11566.8397 5068.6107) (11568.3511 5062.9466) (11572.5038 5058.7939) (11578.1679 5057.2672) (11583.8321 5058.7939)
      (11587.9847 5062.9466) (11589.5115 5068.6107) (11587.9847 5074.2748) (11583.8321 5078.4275) (11578.1679 5079.9389)
      (11572.5038 5078.4275) (11568.3511 5074.2748)
    ))
    ; P3412 -- see feature_dimensions_mm.csv
    ("06_ORNAMENT" 1 (
      (11566.8397 4961.9237) (11568.3511 4956.2595) (11572.5038 4952.1069) (11578.1679 4950.5954) (11583.8321 4952.1069)
      (11587.9847 4956.2595) (11589.5115 4961.9237) (11587.9847 4967.5878) (11583.8321 4971.7405) (11578.1679 4973.2672)
      (11572.5038 4971.7405) (11568.3511 4967.5878)
    ))
    ; P3413 -- see feature_dimensions_mm.csv
    ("06_ORNAMENT" 1 (
      (11566.8397 4366.5038) (11568.3511 4360.8397) (11572.5038 4356.687) (11578.1679 4355.1756) (11583.8321 4356.687)
      (11587.9847 4360.8397) (11589.5115 4366.5038) (11587.9847 4372.1679) (11583.8321 4376.3206) (11578.1679 4377.8473)
      (11572.5038 4376.3206) (11568.3511 4372.1679)
    ))
    ; P3414 -- see feature_dimensions_mm.csv
    ("06_ORNAMENT" 1 (
      (11566.8397 3877.771) (11568.3511 3872.1069) (11572.5038 3867.9542) (11578.1679 3866.4275) (11583.8321 3867.9542)
      (11587.9847 3872.1069) (11589.5115 3877.771) (11587.9847 3883.4351) (11583.8321 3887.5878) (11578.1679 3889.0992)
      (11572.5038 3887.5878) (11568.3511 3883.4351)
    ))
    ; P3415 -- see feature_dimensions_mm.csv
    ("06_ORNAMENT" 1 (
      (11573.2214 5117.4809) (11574.458 5109.6947) (11578.0305 5102.6718) (11583.6031 5097.0992) (11590.626 5093.5267)
      (11598.4122 5092.2901) (11606.1985 5093.5267) (11613.2214 5097.0992) (11618.7939 5102.6718) (11622.3664 5109.6947)
      (11623.6031 5117.4809) (11622.3664 5125.2672) (11618.7939 5132.2901) (11613.2214 5137.8626) (11606.1985 5141.4351)
      (11598.4122 5142.6718) (11590.626 5141.4351) (11583.6031 5137.8626) (11578.0305 5132.2901) (11574.458 5125.2672)
    ))
    ; P3416 -- see feature_dimensions_mm.csv
    ("06_ORNAMENT" 1 (
      (11573.2214 4913.0534) (11574.458 4905.2672) (11578.0305 4898.2443) (11583.6031 4892.6718) (11590.626 4889.0992)
      (11598.4122 4887.8626) (11606.1985 4889.0992) (11613.2214 4892.6718) (11618.7939 4898.2443) (11622.3664 4905.2672)
      (11623.6031 4913.0534) (11622.3664 4920.8397) (11618.7939 4927.8626) (11613.2214 4933.4351) (11606.1985 4937.0076)
      (11598.4122 4938.2443) (11590.626 4937.0076) (11583.6031 4933.4351) (11578.0305 4927.8626) (11574.458 4920.8397)
    ))
    ; P3417 -- see feature_dimensions_mm.csv
    ("06_ORNAMENT" 1 (
      (11573.2214 4522.0611) (11574.458 4514.2748) (11578.0305 4507.2519) (11583.6031 4501.6794) (11590.626 4498.1069)
      (11598.4122 4496.8702) (11606.1985 4498.1069) (11613.2214 4501.6794) (11618.7939 4507.2519) (11622.3664 4514.2748)
      (11623.6031 4522.0611) (11622.3664 4529.8473) (11618.7939 4536.8702) (11613.2214 4542.4427) (11606.1985 4546.0153)
      (11598.4122 4547.2519) (11590.626 4546.0153) (11583.6031 4542.4427) (11578.0305 4536.8702) (11574.458 4529.8473)
    ))
    ; P3418 -- see feature_dimensions_mm.csv
    ("06_ORNAMENT" 1 (
      (11573.2214 4317.6336) (11574.458 4309.8473) (11578.0305 4302.8244) (11583.6031 4297.2519) (11590.626 4293.6794)
      (11598.4122 4292.4427) (11606.1985 4293.6794) (11613.2214 4297.2519) (11618.7939 4302.8244) (11622.3664 4309.8473)
      (11623.6031 4317.6336) (11622.3664 4325.4198) (11618.7939 4332.4427) (11613.2214 4338.0153) (11606.1985 4341.5878)
      (11598.4122 4342.8244) (11590.626 4341.5878) (11583.6031 4338.0153) (11578.0305 4332.4427) (11574.458 4325.4198)
    ))
    ; P3419 -- see feature_dimensions_mm.csv
    ("06_ORNAMENT" 1 (
      (11573.2214 3926.6412) (11574.458 3918.855) (11578.0305 3911.8321) (11583.6031 3906.2595) (11590.626 3902.687)
      (11598.4122 3901.4504) (11606.1985 3902.687) (11613.2214 3906.2595) (11618.7939 3911.8321) (11622.3664 3918.855)
      (11623.6031 3926.6412) (11622.3664 3934.4275) (11618.7939 3941.4504) (11613.2214 3947.0229) (11606.1985 3950.5954)
      (11598.4122 3951.8321) (11590.626 3950.5954) (11583.6031 3947.0229) (11578.0305 3941.4504) (11574.458 3934.4275)
    ))
    ; P3420 -- see feature_dimensions_mm.csv
    ("06_ORNAMENT" 1 (
      (11578.6565 7374.0458) (11579.3588 7370.5496) (11581.3282 7367.5878) (11584.2901 7365.6183) (11587.7863 7364.916)
      (11591.2824 7365.6183) (11594.2443 7367.5878) (11596.2137 7370.5496) (11596.916 7374.0458) (11596.2137 7377.542)
      (11594.2443 7380.5038) (11591.2824 7382.4733) (11587.7863 7383.1756) (11584.2901 7382.4733) (11581.3282 7380.5038)
      (11579.3588 7377.542)
    ))
    ; P3421 -- see feature_dimensions_mm.csv
    ("06_ORNAMENT" 1 (
      (11578.6565 7206.1069) (11579.3588 7202.6107) (11581.3282 7199.6489) (11584.2901 7197.6794) (11587.7863 7196.9771)
      (11591.2824 7197.6794) (11594.2443 7199.6489) (11596.2137 7202.6107) (11596.916 7206.1069) (11596.2137 7209.6031)
      (11594.2443 7212.5649) (11591.2824 7214.5344) (11587.7863 7215.2366) (11584.2901 7214.5344) (11581.3282 7212.5649)
      (11579.3588 7209.6031)
    ))
    ; P3422 -- see feature_dimensions_mm.csv
    ("06_ORNAMENT" 1 (
      (11618.9313 5312.9771) (11620.0916 5301.1756) (11623.5267 5289.8473) (11629.1145 5279.3893) (11636.6412 5270.229)
      (11645.8015 5262.7023) (11656.2595 5257.1145) (11667.5878 5253.6794) (11679.3893 5252.5191) (11691.1908 5253.6794)
      (11702.5191 5257.1145) (11712.9771 5262.7023) (11722.1374 5270.229) (11729.6641 5279.3893) (11735.2519 5289.8473)
      (11738.687 5301.1756) (11739.8473 5312.9771) (11738.687 5324.7786) (11735.2519 5336.1069) (11729.6641 5346.5649)
      (11722.1374 5355.7252) (11712.9771 5363.2519) (11702.5191 5368.8397) (11691.1908 5372.2748) (11679.3893 5373.4351)
      (11667.5878 5372.2748) (11656.2595 5368.8397) (11645.8015 5363.2519) (11636.6412 5355.7252) (11629.1145 5346.5649)
      (11623.5267 5336.1069) (11620.0916 5324.7786)
    ))
    ; P3423 -- see feature_dimensions_mm.csv
    ("06_ORNAMENT" 1 (
      (11618.9313 4717.5573) (11620.0916 4705.7557) (11623.5267 4694.4275) (11629.1145 4683.9695) (11636.6412 4674.8092)
      (11645.8015 4667.2824) (11656.2595 4661.6947) (11667.5878 4658.2595) (11679.3893 4657.0992) (11691.1908 4658.2595)
      (11702.5191 4661.6947) (11712.9771 4667.2824) (11722.1374 4674.8092) (11729.6641 4683.9695) (11735.2519 4694.4275)
      (11738.687 4705.7557) (11739.8473 4717.5573) (11738.687 4729.3588) (11735.2519 4740.687) (11729.6641 4751.145)
      (11722.1374 4760.3053) (11712.9771 4767.8321) (11702.5191 4773.4198) (11691.1908 4776.855) (11679.3893 4778.0153)
      (11667.5878 4776.855) (11656.2595 4773.4198) (11645.8015 4767.8321) (11636.6412 4760.3053) (11629.1145 4751.145)
      (11623.5267 4740.687) (11620.0916 4729.3588)
    ))
    ; P3424 -- see feature_dimensions_mm.csv
    ("06_ORNAMENT" 1 (
      (11618.9313 4122.1374) (11620.0916 4110.3359) (11623.5267 4099.0076) (11629.1145 4088.5496) (11636.6412 4079.3893)
      (11645.8015 4071.8626) (11656.2595 4066.2748) (11667.5878 4062.8397) (11679.3893 4061.6794) (11691.1908 4062.8397)
      (11702.5191 4066.2748) (11712.9771 4071.8626) (11722.1374 4079.3893) (11729.6641 4088.5496) (11735.2519 4099.0076)
      (11738.687 4110.3359) (11739.8473 4122.1374) (11738.687 4133.9389) (11735.2519 4145.2672) (11729.6641 4155.7252)
      (11722.1374 4164.8855) (11712.9771 4172.4122) (11702.5191 4178.0) (11691.1908 4181.4351) (11679.3893 4182.5954)
      (11667.5878 4181.4351) (11656.2595 4178.0) (11645.8015 4172.4122) (11636.6412 4164.8855) (11629.1145 4155.7252)
      (11623.5267 4145.2672) (11620.0916 4133.9389)
    ))
    ; P3425 -- see feature_dimensions_mm.csv
    ("06_ORNAMENT" 1 (
      (11643.3588 3007.6336) (11644.0763 3006.3206) (11646.0 3005.2519) (11648.6412 3004.5496) (11651.2824 3004.1985)
      (11653.2672 3003.9542) (11654.1527 3003.4962) (11653.8473 3002.5649) (11652.6107 3000.9924) (11651.0076 2998.8702)
      (11649.6336 2996.5038) (11649.0076 2994.3817) (11649.4351 2992.9466) (11650.8702 2992.5191) (11652.9924 2993.145)
      (11655.3588 2994.5191) (11657.4809 2996.1221) (11659.0534 2997.3588) (11659.9847 2997.6641) (11660.4427 2996.7786)
      (11660.687 2994.7939) (11661.0382 2992.1527) (11661.7405 2989.5115) (11662.8092 2987.5878) (11664.1221 2986.8702)
      (11665.4351 2987.5878) (11666.5038 2989.5115) (11667.2061 2992.1527) (11667.5573 2994.7939) (11667.8015 2996.7786)
      (11668.2595 2997.6641) (11669.1908 2997.3588) (11670.7634 2996.1221) (11672.8855 2994.5191) (11675.2519 2993.145)
      (11677.374 2992.5191) (11678.8092 2992.9466) (11679.2366 2994.3817) (11678.6107 2996.5038) (11677.2366 2998.8702)
      (11675.6336 3000.9924) (11674.3969 3002.5649) (11674.0916 3003.4962) (11674.9771 3003.9542) (11676.9618 3004.1985)
      (11679.6031 3004.5496) (11682.2443 3005.2519) (11684.1679 3006.3206) (11684.8855 3007.6336) (11684.1679 3008.9466)
      (11682.2443 3010.0153) (11679.6031 3010.7176) (11676.9618 3011.0687) (11674.9771 3011.313) (11674.0916 3011.771)
      (11674.3969 3012.7023) (11675.6336 3014.2748) (11677.2366 3016.3969) (11678.6107 3018.7634) (11679.2366 3020.8855)
      (11678.8092 3022.3206) (11677.374 3022.7481) (11675.2519 3022.1221) (11672.8855 3020.7481) (11670.7634 3019.145)
      (11669.1908 3017.9084) (11668.2595 3017.6031) (11667.8015 3018.4885) (11667.5573 3020.4733) (11667.2061 3023.1145)
      (11666.5038 3025.7557) (11665.4351 3027.6794) (11664.1221 3028.3969) (11662.8092 3027.6794) (11661.7405 3025.7557)
      (11661.0382 3023.1145) (11660.687 3020.4733) (11660.4427 3018.4885) (11659.9847 3017.6031) (11659.0534 3017.9084)
      (11657.4809 3019.145) (11655.3588 3020.7481) (11652.9924 3022.1221) (11650.8702 3022.7481) (11649.4351 3022.3206)
      (11649.0076 3020.8855) (11649.6336 3018.7634) (11651.0076 3016.3969) (11652.6107 3014.2748) (11653.8473 3012.7023)
      (11654.1527 3011.771) (11653.2672 3011.313) (11651.2824 3011.0687) (11648.6412 3010.7176) (11646.0 3010.0153)
      (11644.0763 3008.9466)
    ))
    ; P3426 -- see feature_dimensions_mm.csv
    ("06_ORNAMENT" 1 (
      (11643.3588 2900.7634) (11644.0763 2899.4504) (11646.0 2898.3817) (11648.6412 2897.6794) (11651.2824 2897.3282)
      (11653.2672 2897.084) (11654.1527 2896.626) (11653.8473 2895.6947) (11652.6107 2894.1221) (11651.0076 2892.0)
      (11649.6336 2889.6336) (11649.0076 2887.5115) (11649.4351 2886.0763) (11650.8702 2885.6489) (11652.9924 2886.2748)
      (11655.3588 2887.6489) (11657.4809 2889.2519) (11659.0534 2890.4885) (11659.9847 2890.7939) (11660.4427 2889.9084)
      (11660.687 2887.9237) (11661.0382 2885.2824) (11661.7405 2882.6412) (11662.8092 2880.7176) (11664.1221 2880.0)
      (11665.4351 2880.7176) (11666.5038 2882.6412) (11667.2061 2885.2824) (11667.5573 2887.9237) (11667.8015 2889.9084)
      (11668.2595 2890.7939) (11669.1908 2890.4885) (11670.7634 2889.2519) (11672.8855 2887.6489) (11675.2519 2886.2748)
      (11677.374 2885.6489) (11678.8092 2886.0763) (11679.2366 2887.5115) (11678.6107 2889.6336) (11677.2366 2892.0)
      (11675.6336 2894.1221) (11674.3969 2895.6947) (11674.0916 2896.626) (11674.9771 2897.084) (11676.9618 2897.3282)
      (11679.6031 2897.6794) (11682.2443 2898.3817) (11684.1679 2899.4504) (11684.8855 2900.7634) (11684.1679 2902.0763)
      (11682.2443 2903.145) (11679.6031 2903.8473) (11676.9618 2904.1985) (11674.9771 2904.4427) (11674.0916 2904.9008)
      (11674.3969 2905.8321) (11675.6336 2907.4046) (11677.2366 2909.5267) (11678.6107 2911.8931) (11679.2366 2914.0153)
      (11678.8092 2915.4504) (11677.374 2915.8779) (11675.2519 2915.2519) (11672.8855 2913.8779) (11670.7634 2912.2748)
      (11669.1908 2911.0382) (11668.2595 2910.7328) (11667.8015 2911.6183) (11667.5573 2913.6031) (11667.2061 2916.2443)
      (11666.5038 2918.8855) (11665.4351 2920.8092) (11664.1221 2921.5267) (11662.8092 2920.8092) (11661.7405 2918.8855)
      (11661.0382 2916.2443) (11660.687 2913.6031) (11660.4427 2911.6183) (11659.9847 2910.7328) (11659.0534 2911.0382)
      (11657.4809 2912.2748) (11655.3588 2913.8779) (11652.9924 2915.2519) (11650.8702 2915.8779) (11649.4351 2915.4504)
      (11649.0076 2914.0153) (11649.6336 2911.8931) (11651.0076 2909.5267) (11652.6107 2907.4046) (11653.8473 2905.8321)
      (11654.1527 2904.9008) (11653.2672 2904.4427) (11651.2824 2904.1985) (11648.6412 2903.8473) (11646.0 2903.145)
      (11644.0763 2902.0763)
    ))
    ; P3427 -- see feature_dimensions_mm.csv
    ("06_ORNAMENT" 1 (
      (11644.1221 5312.9771) (11645.3282 5303.8473) (11648.8397 5295.3435) (11654.458 5288.0458) (11661.7557 5282.4275)
      (11670.2595 5278.916) (11679.3893 5277.7099) (11688.5191 5278.916) (11697.0229 5282.4275) (11704.3206 5288.0458)
      (11709.9389 5295.3435) (11713.4504 5303.8473) (11714.6565 5312.9771) (11713.4504 5322.1069) (11709.9389 5330.6107)
      (11704.3206 5337.9084) (11697.0229 5343.5267) (11688.5191 5347.0382) (11679.3893 5348.2443) (11670.2595 5347.0382)
      (11661.7557 5343.5267) (11654.458 5337.9084) (11648.8397 5330.6107) (11645.3282 5322.1069)
    ))
    ; P3428 -- see feature_dimensions_mm.csv
    ("06_ORNAMENT" 1 (
      (11644.1221 4717.5573) (11645.3282 4708.4275) (11648.8397 4699.9237) (11654.458 4692.626) (11661.7557 4687.0076)
      (11670.2595 4683.4962) (11679.3893 4682.2901) (11688.5191 4683.4962) (11697.0229 4687.0076) (11704.3206 4692.626)
      (11709.9389 4699.9237) (11713.4504 4708.4275) (11714.6565 4717.5573) (11713.4504 4726.687) (11709.9389 4735.1908)
      (11704.3206 4742.4885) (11697.0229 4748.1069) (11688.5191 4751.6183) (11679.3893 4752.8244) (11670.2595 4751.6183)
      (11661.7557 4748.1069) (11654.458 4742.4885) (11648.8397 4735.1908) (11645.3282 4726.687)
    ))
    ; P3429 -- see feature_dimensions_mm.csv
    ("06_ORNAMENT" 1 (
      (11644.1221 4122.1374) (11645.3282 4113.0076) (11648.8397 4104.5038) (11654.458 4097.2061) (11661.7557 4091.5878)
      (11670.2595 4088.0763) (11679.3893 4086.8702) (11688.5191 4088.0763) (11697.0229 4091.5878) (11704.3206 4097.2061)
      (11709.9389 4104.5038) (11713.4504 4113.0076) (11714.6565 4122.1374) (11713.4504 4131.2672) (11709.9389 4139.771)
      (11704.3206 4147.0687) (11697.0229 4152.687) (11688.5191 4156.1985) (11679.3893 4157.4046) (11670.2595 4156.1985)
      (11661.7557 4152.687) (11654.458 4147.0687) (11648.8397 4139.771) (11645.3282 4131.2672)
    ))
    ; P3430 -- see feature_dimensions_mm.csv
    ("06_ORNAMENT" 1 (
      (11644.4733 2064.3206) (11646.3511 2052.5344) (11651.771 2041.8931) (11660.2137 2033.4504) (11670.855 2028.0305)
      (11682.6412 2026.1527) (11694.4427 2028.0305) (11705.084 2033.4504) (11713.5267 2041.8931) (11718.9466 2052.5344)
      (11720.8092 2064.3206) (11718.9466 2076.1221) (11713.5267 2086.7634) (11705.084 2095.2061) (11694.4427 2100.626)
      (11682.6412 2102.4885) (11670.855 2100.626) (11660.2137 2095.2061) (11651.771 2086.7634) (11646.3511 2076.1221)
    ))
    ; P3431 -- see feature_dimensions_mm.csv
    ("06_ORNAMENT" 1 (
      (11645.6489 1392.3053) (11646.916 1395.9847) (11648.687 1400.1985) (11651.771 1394.1527) (11659.1603 1386.7634)
      (11656.9618 1387.1603) (11651.6183 1387.8473) (11647.8015 1388.5802) (11645.8168 1389.9237)
    ))
    ; P3432 -- see feature_dimensions_mm.csv
    ("06_ORNAMENT" 1 (
      (11646.6412 5181.9847) (11647.0382 5172.916) (11648.2443 5164.0763) (11650.2137 5155.6794) (11652.9008 5147.9237)
      (11656.229 5141.0229) (11660.1374 5135.1145) (11664.5191 5130.3664) (11669.2672 5126.8855) (11674.2595 5124.7634)
      (11679.3893 5124.0458) (11684.5191 5124.7634) (11689.5115 5126.8855) (11694.2595 5130.3664) (11698.6412 5135.1145)
      (11702.5496 5141.0229) (11705.8779 5147.9237) (11708.5649 5155.6794) (11710.5344 5164.0763) (11711.7405 5172.916)
      (11712.1374 5181.9847) (11711.7405 5191.0534) (11710.5344 5199.8931) (11708.5649 5208.2901) (11705.8779 5216.0458)
      (11702.5496 5222.9466) (11698.6412 5228.855) (11694.2595 5233.6031) (11689.5115 5237.084) (11684.5191 5239.2061)
      (11679.3893 5239.9237) (11674.2595 5239.2061) (11669.2672 5237.084) (11664.5191 5233.6031) (11660.1374 5228.855)
      (11656.229 5222.9466) (11652.9008 5216.0458) (11650.2137 5208.2901) (11648.2443 5199.8931) (11647.0382 5191.0534)
    ))
    ; P3433 -- see feature_dimensions_mm.csv
    ("06_ORNAMENT" 1 (
      (11646.6412 4848.5496) (11647.0382 4839.4809) (11648.2443 4830.6412) (11650.2137 4822.2443) (11652.9008 4814.4885)
      (11656.229 4807.5878) (11660.1374 4801.6794) (11664.5191 4796.9313) (11669.2672 4793.4504) (11674.2595 4791.3282)
      (11679.3893 4790.6107) (11684.5191 4791.3282) (11689.5115 4793.4504) (11694.2595 4796.9313) (11698.6412 4801.6794)
      (11702.5496 4807.5878) (11705.8779 4814.4885) (11708.5649 4822.2443) (11710.5344 4830.6412) (11711.7405 4839.4809)
      (11712.1374 4848.5496) (11711.7405 4857.6183) (11710.5344 4866.458) (11708.5649 4874.855) (11705.8779 4882.6107)
      (11702.5496 4889.5115) (11698.6412 4895.4198) (11694.2595 4900.1679) (11689.5115 4903.6489) (11684.5191 4905.771)
      (11679.3893 4906.4885) (11674.2595 4905.771) (11669.2672 4903.6489) (11664.5191 4900.1679) (11660.1374 4895.4198)
      (11656.229 4889.5115) (11652.9008 4882.6107) (11650.2137 4874.855) (11648.2443 4866.458) (11647.0382 4857.6183)
    ))
    ; P3434 -- see feature_dimensions_mm.csv
    ("06_ORNAMENT" 1 (
      (11646.6412 4253.1298) (11647.0382 4244.0611) (11648.2443 4235.2214) (11650.2137 4226.8244) (11652.9008 4219.0687)
      (11656.229 4212.1679) (11660.1374 4206.2595) (11664.5191 4201.5115) (11669.2672 4198.0305) (11674.2595 4195.9084)
      (11679.3893 4195.1908) (11684.5191 4195.9084) (11689.5115 4198.0305) (11694.2595 4201.5115) (11698.6412 4206.2595)
      (11702.5496 4212.1679) (11705.8779 4219.0687) (11708.5649 4226.8244) (11710.5344 4235.2214) (11711.7405 4244.0611)
      (11712.1374 4253.1298) (11711.7405 4262.1985) (11710.5344 4271.0382) (11708.5649 4279.4351) (11705.8779 4287.1908)
      (11702.5496 4294.0916) (11698.6412 4300.0) (11694.2595 4304.7481) (11689.5115 4308.229) (11684.5191 4310.3511)
      (11679.3893 4311.0687) (11674.2595 4310.3511) (11669.2672 4308.229) (11664.5191 4304.7481) (11660.1374 4300.0)
      (11656.229 4294.0916) (11652.9008 4287.1908) (11650.2137 4279.4351) (11648.2443 4271.0382) (11647.0382 4262.1985)
    ))
    ; P3435 -- see feature_dimensions_mm.csv
    ("06_ORNAMENT" 1 (
      (11646.6412 3991.145) (11647.0382 3982.0763) (11648.2443 3973.2366) (11650.2137 3964.8397) (11652.9008 3957.084)
      (11656.229 3950.1832) (11660.1374 3944.2748) (11664.5191 3939.5267) (11669.2672 3936.0458) (11674.2595 3933.9237)
      (11679.3893 3933.2061) (11684.5191 3933.9237) (11689.5115 3936.0458) (11694.2595 3939.5267) (11698.6412 3944.2748)
      (11702.5496 3950.1832) (11705.8779 3957.084) (11708.5649 3964.8397) (11710.5344 3973.2366) (11711.7405 3982.0763)
      (11712.1374 3991.145) (11711.7405 4000.2137) (11710.5344 4009.0534) (11708.5649 4017.4504) (11705.8779 4025.2061)
      (11702.5496 4032.1069) (11698.6412 4038.0153) (11694.2595 4042.7634) (11689.5115 4046.2443) (11684.5191 4048.3664)
      (11679.3893 4049.084) (11674.2595 4048.3664) (11669.2672 4046.2443) (11664.5191 4042.7634) (11660.1374 4038.0153)
      (11656.229 4032.1069) (11652.9008 4025.2061) (11650.2137 4017.4504) (11648.2443 4009.0534) (11647.0382 4000.2137)
    ))
    ; P3436 -- see feature_dimensions_mm.csv
    ("06_ORNAMENT" 1 (
      (11658.0153 3007.6336) (11658.4733 3005.2977) (11659.8015 3003.313) (11661.7863 3001.9847) (11664.1221 3001.5267)
      (11666.458 3001.9847) (11668.4427 3003.313) (11669.771 3005.2977) (11670.229 3007.6336) (11669.771 3009.9695)
      (11668.4427 3011.9542) (11666.458 3013.2824) (11664.1221 3013.7405) (11661.7863 3013.2824) (11659.8015 3011.9542)
      (11658.4733 3009.9695)
    ))
    ; P3437 -- see feature_dimensions_mm.csv
    ("06_ORNAMENT" 1 (
      (11658.0153 2900.7634) (11658.4733 2898.4275) (11659.8015 2896.4427) (11661.7863 2895.1145) (11664.1221 2894.6565)
      (11666.458 2895.1145) (11668.4427 2896.4427) (11669.771 2898.4275) (11670.229 2900.7634) (11669.771 2903.0992)
      (11668.4427 2905.084) (11666.458 2906.4122) (11664.1221 2906.8702) (11661.7863 2906.4122) (11659.8015 2905.084)
      (11658.4733 2903.0992)
    ))
    ; P3438 -- see feature_dimensions_mm.csv
    ("06_ORNAMENT" 1 (
      (11664.1221 6045.8015) (11680.5038 6034.5038) (11699.0534 6023.0534) (11719.4962 6011.6183) (11741.4962 6000.3817)
      (11764.7786 5989.542) (11789.0229 5979.2519) (11813.9542 5969.7099) (11839.2366 5961.084) (11864.5802 5953.5725)
      (11889.6947 5947.3435) (11914.2595 5942.5954) (11937.9847 5939.4809) (11947.6489 5938.9313) (11981.6794 5938.9313)
      (11963.9847 5952.7328) (11944.0458 5965.7557) (11922.2137 5977.9847) (11898.8702 5989.3435) (11874.3969 5999.8015)
      (11849.1603 6009.313) (11823.5115 6017.8321) (11797.8473 6025.313) (11772.5344 6031.7099) (11747.9389 6036.9618)
      (11724.4275 6041.0534) (11702.3664 6043.9237) (11682.1374 6045.5115)
    ))
    ; P3439 -- see feature_dimensions_mm.csv
    ("06_ORNAMENT" 1 (
      (11666.3817 1594.6565) (11668.0 1585.374) (11671.542 1575.9389) (11676.9313 1566.6107) (11684.0458 1557.6031)
      (11692.7023 1549.1298) (11702.687 1541.4198) (11713.7557 1534.6565) (11725.6336 1529.0076) (11738.0305 1524.6107)
      (11750.6412 1521.5725) (11763.145 1519.9542) (11775.2519 1519.8168) (11786.6565 1521.1603) (11797.0687 1523.9389)
      (11806.2443 1528.1069) (11813.9542 1533.542) (11816.7939 1536.626) (11816.7939 1592.2901) (11816.3969 1592.9771)
      (11809.2824 1601.9847) (11800.626 1610.4427) (11790.6412 1618.1527) (11779.5725 1624.916) (11767.6947 1630.5649)
      (11755.2977 1634.9618) (11742.7023 1638.0153) (11730.1832 1639.6183) (11718.0916 1639.7557) (11706.687 1638.4122)
      (11696.2748 1635.6336) (11687.0992 1631.4809) (11679.3893 1626.0458) (11673.3282 1619.4656) (11669.084 1611.9237)
      (11666.7481 1603.5878)
    ))
    ; P3440 -- see feature_dimensions_mm.csv
    ("06_ORNAMENT" 1 (
      (11668.0611 5048.4733) (11669.5725 5042.8092) (11673.7252 5038.6565) (11679.3893 5037.1298) (11685.0534 5038.6565)
      (11689.2061 5042.8092) (11690.7328 5048.4733) (11689.2061 5054.1374) (11685.0534 5058.2901) (11679.3893 5059.8015)
      (11673.7252 5058.2901) (11669.5725 5054.1374)
    ))
    ; P3441 -- see feature_dimensions_mm.csv
    ("06_ORNAMENT" 1 (
      (11668.0611 3857.6336) (11669.5725 3851.9695) (11673.7252 3847.8168) (11679.3893 3846.2901) (11685.0534 3847.8168)
      (11689.2061 3851.9695) (11690.7328 3857.6336) (11689.2061 3863.2977) (11685.0534 3867.4504) (11679.3893 3868.9618)
      (11673.7252 3867.4504) (11669.5725 3863.2977)
    ))
    ; P3442 -- see feature_dimensions_mm.csv
    ("06_ORNAMENT" 1 (
      (11724.9924 5379.6183) (11725.8931 5373.8015) (11727.9237 5368.7634) (11731.0534 5364.6412) (11735.1756 5361.5115)
      (11740.2137 5359.4809) (11746.0305 5358.5802) (11752.4885 5358.8397) (11759.4198 5360.2595) (11766.6718 5362.7939)
      (11774.0458 5366.3664) (11781.374 5370.916) (11788.4733 5376.3206) (11795.1756 5382.4427) (11801.2977 5389.145)
      (11806.7023 5396.2443) (11811.2519 5403.5725) (11814.8244 5410.9466) (11817.3588 5418.1985) (11818.7634 5425.1298)
      (11819.0382 5431.5878) (11818.1374 5437.4046) (11816.1069 5442.4427) (11812.9771 5446.5649) (11808.855 5449.6947)
      (11803.8168 5451.7252) (11798.0 5452.626) (11791.542 5452.3511) (11784.6107 5450.9466) (11777.3588 5448.4122)
      (11769.9847 5444.8397) (11762.6565 5440.2901) (11755.5573 5434.8855) (11748.855 5428.7634) (11742.7328 5422.0611)
      (11737.3282 5414.9618) (11732.7786 5407.6336) (11729.2061 5400.2595) (11726.6718 5393.0076) (11725.2519 5386.0763)
    ))
    ; P3443 -- see feature_dimensions_mm.csv
    ("06_ORNAMENT" 1 (
      (11724.9924 5246.3359) (11725.2519 5239.8779) (11726.6718 5232.9466) (11729.2061 5225.6947) (11732.7786 5218.3206)
      (11737.3282 5210.9924) (11742.7328 5203.8931) (11748.855 5197.1908) (11755.5573 5191.0687) (11762.6565 5185.6641)
      (11769.9847 5181.1145) (11777.3588 5177.542) (11784.6107 5175.0076) (11791.542 5173.6031) (11798.0 5173.3282)
      (11803.8168 5174.229) (11808.855 5176.2595) (11812.9771 5179.3893) (11816.1069 5183.5115) (11818.1374 5188.5496)
      (11819.0382 5194.3664) (11818.7634 5200.8244) (11817.3588 5207.7557) (11814.8244 5215.0076) (11811.2519 5222.3817)
      (11806.7023 5229.7099) (11801.2977 5236.8092) (11795.1756 5243.5115) (11788.4733 5249.6336) (11781.374 5255.0382)
      (11774.0458 5259.5878) (11766.6718 5263.1603) (11759.4198 5265.6947) (11752.4885 5267.1145) (11746.0305 5267.374)
      (11740.2137 5266.4733) (11735.1756 5264.4427) (11731.0534 5261.313) (11727.9237 5257.1908) (11725.8931 5252.1527)
    ))
    ; P3444 -- see feature_dimensions_mm.csv
    ("06_ORNAMENT" 1 (
      (11724.9924 4784.1985) (11725.8931 4778.3817) (11727.9237 4773.3435) (11731.0534 4769.2214) (11735.1756 4766.0916)
      (11740.2137 4764.0611) (11746.0305 4763.1603) (11752.4885 4763.4198) (11759.4198 4764.8397) (11766.6718 4767.374)
      (11774.0458 4770.9466) (11781.374 4775.4962) (11788.4733 4780.9008) (11795.1756 4787.0229) (11801.2977 4793.7252)
      (11806.7023 4800.8244) (11811.2519 4808.1527) (11814.8244 4815.5267) (11817.3588 4822.7786) (11818.7634 4829.7099)
      (11819.0382 4836.1679) (11818.1374 4841.9847) (11816.1069 4847.0229) (11812.9771 4851.145) (11808.855 4854.2748)
      (11803.8168 4856.3053) (11798.0 4857.2061) (11791.542 4856.9313) (11784.6107 4855.5267) (11777.3588 4852.9924)
      (11769.9847 4849.4198) (11762.6565 4844.8702) (11755.5573 4839.4656) (11748.855 4833.3435) (11742.7328 4826.6412)
      (11737.3282 4819.542) (11732.7786 4812.2137) (11729.2061 4804.8397) (11726.6718 4797.5878) (11725.2519 4790.6565)
    ))
    ; P3445 -- see feature_dimensions_mm.csv
    ("06_ORNAMENT" 1 (
      (11724.9924 4650.916) (11725.2519 4644.458) (11726.6718 4637.5267) (11729.2061 4630.2748) (11732.7786 4622.9008)
      (11737.3282 4615.5725) (11742.7328 4608.4733) (11748.855 4601.771) (11755.5573 4595.6489) (11762.6565 4590.2443)
      (11769.9847 4585.6947) (11777.3588 4582.1221) (11784.6107 4579.5878) (11791.542 4578.1832) (11798.0 4577.9084)
      (11803.8168 4578.8092) (11808.855 4580.8397) (11812.9771 4583.9695) (11816.1069 4588.0916) (11818.1374 4593.1298)
      (11819.0382 4598.9466) (11818.7634 4605.4046) (11817.3588 4612.3359) (11814.8244 4619.5878) (11811.2519 4626.9618)
      (11806.7023 4634.2901) (11801.2977 4641.3893) (11795.1756 4648.0916) (11788.4733 4654.2137) (11781.374 4659.6183)
      (11774.0458 4664.1679) (11766.6718 4667.7405) (11759.4198 4670.2748) (11752.4885 4671.6947) (11746.0305 4671.9542)
      (11740.2137 4671.0534) (11735.1756 4669.0229) (11731.0534 4665.8931) (11727.9237 4661.771) (11725.8931 4656.7328)
    ))
    ; P3446 -- see feature_dimensions_mm.csv
    ("06_ORNAMENT" 1 (
      (11724.9924 4188.7786) (11725.8931 4182.9618) (11727.9237 4177.9237) (11731.0534 4173.8015) (11735.1756 4170.6718)
      (11740.2137 4168.6412) (11746.0305 4167.7405) (11752.4885 4168.0) (11759.4198 4169.4198) (11766.6718 4171.9542)
      (11774.0458 4175.5267) (11781.374 4180.0763) (11788.4733 4185.4809) (11795.1756 4191.6031) (11801.2977 4198.3053)
      (11806.7023 4205.4046) (11811.2519 4212.7328) (11814.8244 4220.1069) (11817.3588 4227.3588) (11818.7634 4234.2901)
      (11819.0382 4240.7481) (11818.1374 4246.5649) (11816.1069 4251.6031) (11812.9771 4255.7252) (11808.855 4258.855)
      (11803.8168 4260.8855) (11798.0 4261.7863) (11791.542 4261.5115) (11784.6107 4260.1069) (11777.3588 4257.5725)
      (11769.9847 4254.0) (11762.6565 4249.4504) (11755.5573 4244.0458) (11748.855 4237.9237) (11742.7328 4231.2214)
      (11737.3282 4224.1221) (11732.7786 4216.7939) (11729.2061 4209.4198) (11726.6718 4202.1679) (11725.2519 4195.2366)
    ))
    ; P3447 -- see feature_dimensions_mm.csv
    ("06_ORNAMENT" 1 (
      (11724.9924 4055.4962) (11725.2519 4049.0382) (11726.6718 4042.1069) (11729.2061 4034.855) (11732.7786 4027.4809)
      (11737.3282 4020.1527) (11742.7328 4013.0534) (11748.855 4006.3511) (11755.5573 4000.229) (11762.6565 3994.8244)
      (11769.9847 3990.2748) (11777.3588 3986.7023) (11784.6107 3984.1679) (11791.542 3982.7634) (11798.0 3982.4885)
      (11803.8168 3983.3893) (11808.855 3985.4198) (11812.9771 3988.5496) (11816.1069 3992.6718) (11818.1374 3997.7099)
      (11819.0382 4003.5267) (11818.7634 4009.9847) (11817.3588 4016.916) (11814.8244 4024.1679) (11811.2519 4031.542)
      (11806.7023 4038.8702) (11801.2977 4045.9695) (11795.1756 4052.6718) (11788.4733 4058.7939) (11781.374 4064.1985)
      (11774.0458 4068.7481) (11766.6718 4072.3206) (11759.4198 4074.855) (11752.4885 4076.2748) (11746.0305 4076.5344)
      (11740.2137 4075.6336) (11735.1756 4073.6031) (11731.0534 4070.4733) (11727.9237 4066.3511) (11725.8931 4061.313)
    ))
    ; P3448 -- see feature_dimensions_mm.csv
    ("06_ORNAMENT" 1 (
      (11735.1756 5117.4809) (11736.4122 5109.6947) (11739.9847 5102.6718) (11745.5573 5097.0992) (11752.5802 5093.5267)
      (11760.3664 5092.2901) (11768.1527 5093.5267) (11775.1756 5097.0992) (11780.7481 5102.6718) (11784.3206 5109.6947)
      (11785.5573 5117.4809) (11784.3206 5125.2672) (11780.7481 5132.2901) (11775.1756 5137.8626) (11768.1527 5141.4351)
      (11760.3664 5142.6718) (11752.5802 5141.4351) (11745.5573 5137.8626) (11739.9847 5132.2901) (11736.4122 5125.2672)
    ))
    ; P3449 -- see feature_dimensions_mm.csv
    ("06_ORNAMENT" 1 (
      (11735.1756 4913.0534) (11736.4122 4905.2672) (11739.9847 4898.2443) (11745.5573 4892.6718) (11752.5802 4889.0992)
      (11760.3664 4887.8626) (11768.1527 4889.0992) (11775.1756 4892.6718) (11780.7481 4898.2443) (11784.3206 4905.2672)
      (11785.5573 4913.0534) (11784.3206 4920.8397) (11780.7481 4927.8626) (11775.1756 4933.4351) (11768.1527 4937.0076)
      (11760.3664 4938.2443) (11752.5802 4937.0076) (11745.5573 4933.4351) (11739.9847 4927.8626) (11736.4122 4920.8397)
    ))
    ; P3450 -- see feature_dimensions_mm.csv
    ("06_ORNAMENT" 1 (
      (11735.1756 4522.0611) (11736.4122 4514.2748) (11739.9847 4507.2519) (11745.5573 4501.6794) (11752.5802 4498.1069)
      (11760.3664 4496.8702) (11768.1527 4498.1069) (11775.1756 4501.6794) (11780.7481 4507.2519) (11784.3206 4514.2748)
      (11785.5573 4522.0611) (11784.3206 4529.8473) (11780.7481 4536.8702) (11775.1756 4542.4427) (11768.1527 4546.0153)
      (11760.3664 4547.2519) (11752.5802 4546.0153) (11745.5573 4542.4427) (11739.9847 4536.8702) (11736.4122 4529.8473)
    ))
    ; P3451 -- see feature_dimensions_mm.csv
    ("06_ORNAMENT" 1 (
      (11735.1756 4317.6336) (11736.4122 4309.8473) (11739.9847 4302.8244) (11745.5573 4297.2519) (11752.5802 4293.6794)
      (11760.3664 4292.4427) (11768.1527 4293.6794) (11775.1756 4297.2519) (11780.7481 4302.8244) (11784.3206 4309.8473)
      (11785.5573 4317.6336) (11784.3206 4325.4198) (11780.7481 4332.4427) (11775.1756 4338.0153) (11768.1527 4341.5878)
      (11760.3664 4342.8244) (11752.5802 4341.5878) (11745.5573 4338.0153) (11739.9847 4332.4427) (11736.4122 4325.4198)
    ))
    ; P3452 -- see feature_dimensions_mm.csv
    ("06_ORNAMENT" 1 (
      (11735.1756 3926.6412) (11736.4122 3918.855) (11739.9847 3911.8321) (11745.5573 3906.2595) (11752.5802 3902.687)
      (11760.3664 3901.4504) (11768.1527 3902.687) (11775.1756 3906.2595) (11780.7481 3911.8321) (11784.3206 3918.855)
      (11785.5573 3926.6412) (11784.3206 3934.4275) (11780.7481 3941.4504) (11775.1756 3947.0229) (11768.1527 3950.5954)
      (11760.3664 3951.8321) (11752.5802 3950.5954) (11745.5573 3947.0229) (11739.9847 3941.4504) (11736.4122 3934.4275)
    ))
    ; P3453 -- see feature_dimensions_mm.csv
    ("06_ORNAMENT" 1 (
      (11752.4427 5312.9771) (11753.1603 5307.8473) (11755.2824 5302.855) (11758.7634 5298.1069) (11763.5115 5293.7252)
      (11769.4198 5289.8168) (11776.3206 5286.4885) (11784.0763 5283.8015) (11792.4733 5281.8321) (11801.313 5280.626)
      (11810.3817 5280.229) (11819.4504 5280.626) (11828.2901 5281.8321) (11836.687 5283.8015) (11844.4427 5286.4885)
      (11851.3435 5289.8168) (11857.2519 5293.7252) (11862.0 5298.1069) (11865.4809 5302.855) (11867.6031 5307.8473)
      (11868.3206 5312.9771) (11867.6031 5318.1069) (11865.4809 5323.0992) (11862.0 5327.8473) (11857.2519 5332.229)
      (11851.3435 5336.1374) (11844.4427 5339.4656) (11836.687 5342.1527) (11828.2901 5344.1221) (11819.4504 5345.3282)
      (11810.3817 5345.7252) (11801.313 5345.3282) (11792.4733 5344.1221) (11784.0763 5342.1527) (11776.3206 5339.4656)
      (11769.4198 5336.1374) (11763.5115 5332.229) (11758.7634 5327.8473) (11755.2824 5323.0992) (11753.1603 5318.1069)
    ))
    ; P3454 -- see feature_dimensions_mm.csv
    ("06_ORNAMENT" 1 (
      (11752.4427 4717.5573) (11753.1603 4712.4275) (11755.2824 4707.4351) (11758.7634 4702.687) (11763.5115 4698.3053)
      (11769.4198 4694.3969) (11776.3206 4691.0687) (11784.0763 4688.3817) (11792.4733 4686.4122) (11801.313 4685.2061)
      (11810.3817 4684.8092) (11819.4504 4685.2061) (11828.2901 4686.4122) (11836.687 4688.3817) (11844.4427 4691.0687)
      (11851.3435 4694.3969) (11857.2519 4698.3053) (11862.0 4702.687) (11865.4809 4707.4351) (11867.6031 4712.4275)
      (11868.3206 4717.5573) (11867.6031 4722.687) (11865.4809 4727.6794) (11862.0 4732.4275) (11857.2519 4736.8092)
      (11851.3435 4740.7176) (11844.4427 4744.0458) (11836.687 4746.7328) (11828.2901 4748.7023) (11819.4504 4749.9084)
      (11810.3817 4750.3053) (11801.313 4749.9084) (11792.4733 4748.7023) (11784.0763 4746.7328) (11776.3206 4744.0458)
      (11769.4198 4740.7176) (11763.5115 4736.8092) (11758.7634 4732.4275) (11755.2824 4727.6794) (11753.1603 4722.687)
    ))
    ; P3455 -- see feature_dimensions_mm.csv
    ("06_ORNAMENT" 1 (
      (11752.4427 4122.1374) (11753.1603 4117.0076) (11755.2824 4112.0153) (11758.7634 4107.2672) (11763.5115 4102.8855)
      (11769.4198 4098.9771) (11776.3206 4095.6489) (11784.0763 4092.9618) (11792.4733 4090.9924) (11801.313 4089.7863)
      (11810.3817 4089.3893) (11819.4504 4089.7863) (11828.2901 4090.9924) (11836.687 4092.9618) (11844.4427 4095.6489)
      (11851.3435 4098.9771) (11857.2519 4102.8855) (11862.0 4107.2672) (11865.4809 4112.0153) (11867.6031 4117.0076)
      (11868.3206 4122.1374) (11867.6031 4127.2672) (11865.4809 4132.2595) (11862.0 4137.0076) (11857.2519 4141.3893)
      (11851.3435 4145.2977) (11844.4427 4148.626) (11836.687 4151.313) (11828.2901 4153.2824) (11819.4504 4154.4885)
      (11810.3817 4154.8855) (11801.313 4154.4885) (11792.4733 4153.2824) (11784.0763 4151.313) (11776.3206 4148.626)
      (11769.4198 4145.2977) (11763.5115 4141.3893) (11758.7634 4137.0076) (11755.2824 4132.2595) (11753.1603 4127.2672)
    ))
    ; P3456 -- see feature_dimensions_mm.csv
    ("06_ORNAMENT" 1 (
      (11769.2672 5068.6107) (11770.7939 5062.9466) (11774.9466 5058.7939) (11780.6107 5057.2672) (11786.2748 5058.7939)
      (11790.4275 5062.9466) (11791.9389 5068.6107) (11790.4275 5074.2748) (11786.2748 5078.4275) (11780.6107 5079.9389)
      (11774.9466 5078.4275) (11770.7939 5074.2748)
    ))
    ; P3457 -- see feature_dimensions_mm.csv
    ("06_ORNAMENT" 1 (
      (11769.2672 4961.9237) (11770.7939 4956.2595) (11774.9466 4952.1069) (11780.6107 4950.5954) (11786.2748 4952.1069)
      (11790.4275 4956.2595) (11791.9389 4961.9237) (11790.4275 4967.5878) (11786.2748 4971.7405) (11780.6107 4973.2672)
      (11774.9466 4971.7405) (11770.7939 4967.5878)
    ))
    ; P3458 -- see feature_dimensions_mm.csv
    ("06_ORNAMENT" 1 (
      (11769.2672 4366.5038) (11770.7939 4360.8397) (11774.9466 4356.687) (11780.6107 4355.1756) (11786.2748 4356.687)
      (11790.4275 4360.8397) (11791.9389 4366.5038) (11790.4275 4372.1679) (11786.2748 4376.3206) (11780.6107 4377.8473)
      (11774.9466 4376.3206) (11770.7939 4372.1679)
    ))
    ; P3459 -- see feature_dimensions_mm.csv
    ("06_ORNAMENT" 1 (
      (11769.2672 3877.771) (11770.7939 3872.1069) (11774.9466 3867.9542) (11780.6107 3866.4275) (11786.2748 3867.9542)
      (11790.4275 3872.1069) (11791.9389 3877.771) (11790.4275 3883.4351) (11786.2748 3887.5878) (11780.6107 3889.0992)
      (11774.9466 3887.5878) (11770.7939 3883.4351)
    ))
    ; P3460 -- see feature_dimensions_mm.csv
    ("06_ORNAMENT" 1 (
      (11777.0992 5022.9008) (11777.5115 5020.3206) (11778.7023 5017.8931) (11780.5954 5015.6947) (11783.0534 5013.8626)
      (11785.8931 5012.4122) (11788.916 5011.3588) (11791.9542 5010.6412) (11794.7939 5010.1985) (11797.313 5009.8779)
      (11799.4046 5009.5573) (11801.0382 5009.084) (11802.1985 5008.3053) (11802.9771 5007.145) (11803.4504 5005.5115)
      (11803.771 5003.4198) (11804.0916 5000.9008) (11804.5344 4998.0611) (11805.2519 4995.0229) (11806.3053 4992.0)
      (11807.7557 4989.1603) (11809.5878 4986.7023) (11811.7863 4984.8092) (11814.2137 4983.6183) (11816.7939 4983.2061)
      (11819.374 4983.6183) (11821.8015 4984.8092) (11824.0 4986.7023) (11825.8321 4989.1603) (11827.2824 4992.0)
      (11828.3359 4995.0229) (11829.0534 4998.0611) (11829.4962 5000.9008) (11829.8168 5003.4198) (11830.1374 5005.5115)
      (11830.6107 5007.145) (11831.3893 5008.3053) (11832.5496 5009.084) (11834.1832 5009.5573) (11836.2748 5009.8779)
      (11838.7939 5010.1985) (11841.6336 5010.6412) (11844.6718 5011.3588) (11847.6947 5012.4122) (11850.5344 5013.8626)
      (11852.9924 5015.6947) (11854.8855 5017.8931) (11856.0763 5020.3206) (11856.4885 5022.9008) (11856.0763 5025.4809)
      (11854.8855 5027.9084) (11852.9924 5030.1069) (11850.5344 5031.9389) (11847.6947 5033.3893) (11844.6718 5034.4427)
      (11841.6336 5035.1603) (11838.7939 5035.6031) (11836.2748 5035.9237) (11834.1832 5036.2443) (11832.5496 5036.7176)
      (11831.3893 5037.4962) (11830.6107 5038.6565) (11830.1374 5040.2901) (11829.8168 5042.3817) (11829.4962 5044.9008)
      (11829.0534 5047.7405) (11828.3359 5050.7786) (11827.2824 5053.8015) (11825.8321 5056.6412) (11824.0 5059.0992)
      (11821.8015 5060.9924) (11819.374 5062.1832) (11816.7939 5062.5954) (11814.2137 5062.1832) (11811.7863 5060.9924)
      (11809.5878 5059.0992) (11807.7557 5056.6412) (11806.3053 5053.8015) (11805.2519 5050.7786) (11804.5344 5047.7405)
      (11804.0916 5044.9008) (11803.771 5042.3817) (11803.4504 5040.2901) (11802.9771 5038.6565) (11802.1985 5037.4962)
      (11801.0382 5036.7176) (11799.4046 5036.2443) (11797.313 5035.9237) (11794.7939 5035.6031) (11791.9542 5035.1603)
      (11788.916 5034.4427) (11785.8931 5033.3893) (11783.0534 5031.9389) (11780.5954 5030.1069) (11778.7023 5027.9084)
      (11777.5115 5025.4809)
    ))
    ; P3461 -- see feature_dimensions_mm.csv
    ("06_ORNAMENT" 1 (
      (11778.626 1740.458) (11780.4885 1728.6565) (11785.9084 1718.0305) (11794.3664 1709.5725) (11804.9924 1704.1527)
      (11816.7939 1702.2901) (11816.7939 1778.626) (11804.9924 1776.7634) (11794.3664 1771.3435) (11785.9084 1762.8855)
      (11780.4885 1752.2595)
    ))
    ; P3462 -- see feature_dimensions_mm.csv
    ("06_ORNAMENT" 1 (
      (11786.2595 6137.4046) (11795.1298 6122.0153) (11805.771 6105.771) (11817.9695 6088.9313) (11831.5725 6071.7557)
      (11846.4122 6054.5191) (11862.2901 6037.4656) (11879.0534 6020.855) (11896.5191 6004.9466) (11914.4885 5990.0153)
      (11932.8244 5976.3053) (11951.3282 5964.0916) (11969.8168 5953.6031) (11988.1374 5945.1298) (12006.1069 5938.9313)
      (11997.1908 5956.9924) (11986.0763 5975.0992) (11973.0382 5993.084) (11958.3817 6010.8092) (11942.3817 6028.0763)
      (11925.3435 6044.7634) (11907.542 6060.687) (11889.2824 6075.6947) (11870.855 6089.6336) (11852.5344 6102.3053)
      (11834.626 6113.5878) (11817.4198 6123.313) (11801.1908 6131.2977)
    ))
    ; P3463 -- see feature_dimensions_mm.csv
    ("06_ORNAMENT" 1 (
      (11849.6947 5393.9542) (11850.9313 5386.1679) (11854.5038 5379.145) (11860.0763 5373.5725) (11867.0992 5370.0)
      (11874.8855 5368.7634) (11882.6718 5370.0) (11889.6947 5373.5725) (11895.2672 5379.145) (11898.8397 5386.1679)
      (11900.0763 5393.9542) (11898.8397 5401.7405) (11895.2672 5408.7634) (11889.6947 5414.3359) (11882.6718 5417.9084)
      (11874.8855 5419.145) (11867.0992 5417.9084) (11860.0763 5414.3359) (11854.5038 5408.7634) (11850.9313 5401.7405)
    ))
    ; P3464 -- see feature_dimensions_mm.csv
    ("06_ORNAMENT" 1 (
      (11849.6947 5232.0) (11850.9313 5224.2137) (11854.5038 5217.1908) (11860.0763 5211.6183) (11867.0992 5208.0458)
      (11874.8855 5206.8092) (11882.6718 5208.0458) (11889.6947 5211.6183) (11895.2672 5217.1908) (11898.8397 5224.2137)
      (11900.0763 5232.0) (11898.8397 5239.7863) (11895.2672 5246.8092) (11889.6947 5252.3817) (11882.6718 5255.9542)
      (11874.8855 5257.1908) (11867.0992 5255.9542) (11860.0763 5252.3817) (11854.5038 5246.8092) (11850.9313 5239.7863)
    ))
    ; P3465 -- see feature_dimensions_mm.csv
    ("06_ORNAMENT" 1 (
      (11849.6947 4798.5344) (11850.9313 4790.7481) (11854.5038 4783.7252) (11860.0763 4778.1527) (11867.0992 4774.5802)
      (11874.8855 4773.3435) (11882.6718 4774.5802) (11889.6947 4778.1527) (11895.2672 4783.7252) (11898.8397 4790.7481)
      (11900.0763 4798.5344) (11898.8397 4806.3206) (11895.2672 4813.3435) (11889.6947 4818.916) (11882.6718 4822.4885)
      (11874.8855 4823.7252) (11867.0992 4822.4885) (11860.0763 4818.916) (11854.5038 4813.3435) (11850.9313 4806.3206)
    ))
    ; P3466 -- see feature_dimensions_mm.csv
    ("06_ORNAMENT" 1 (
      (11849.6947 4636.5802) (11850.9313 4628.7939) (11854.5038 4621.771) (11860.0763 4616.1985) (11867.0992 4612.626)
      (11874.8855 4611.3893) (11882.6718 4612.626) (11889.6947 4616.1985) (11895.2672 4621.771) (11898.8397 4628.7939)
      (11900.0763 4636.5802) (11898.8397 4644.3664) (11895.2672 4651.3893) (11889.6947 4656.9618) (11882.6718 4660.5344)
      (11874.8855 4661.771) (11867.0992 4660.5344) (11860.0763 4656.9618) (11854.5038 4651.3893) (11850.9313 4644.3664)
    ))
    ; P3467 -- see feature_dimensions_mm.csv
    ("06_ORNAMENT" 1 (
      (11849.6947 4203.1145) (11850.9313 4195.3282) (11854.5038 4188.3053) (11860.0763 4182.7328) (11867.0992 4179.1603)
      (11874.8855 4177.9237) (11882.6718 4179.1603) (11889.6947 4182.7328) (11895.2672 4188.3053) (11898.8397 4195.3282)
      (11900.0763 4203.1145) (11898.8397 4210.9008) (11895.2672 4217.9237) (11889.6947 4223.4962) (11882.6718 4227.0687)
      (11874.8855 4228.3053) (11867.0992 4227.0687) (11860.0763 4223.4962) (11854.5038 4217.9237) (11850.9313 4210.9008)
    ))
    ; P3468 -- see feature_dimensions_mm.csv
    ("06_ORNAMENT" 1 (
      (11849.6947 4041.1603) (11850.9313 4033.374) (11854.5038 4026.3511) (11860.0763 4020.7786) (11867.0992 4017.2061)
      (11874.8855 4015.9695) (11882.6718 4017.2061) (11889.6947 4020.7786) (11895.2672 4026.3511) (11898.8397 4033.374)
      (11900.0763 4041.1603) (11898.8397 4048.9466) (11895.2672 4055.9695) (11889.6947 4061.542) (11882.6718 4065.1145)
      (11874.8855 4066.3511) (11867.0992 4065.1145) (11860.0763 4061.542) (11854.5038 4055.9695) (11850.9313 4048.9466)
    ))
    ; P3469 -- see feature_dimensions_mm.csv
    ("06_ORNAMENT" 1 (
      (11855.084 5500.0153) (11856.6107 5494.3359) (11860.7481 5490.1985) (11866.4275 5488.6718) (11872.0916 5490.1985)
      (11876.2443 5494.3359) (11877.7557 5500.0153) (11876.2443 5505.6794) (11872.0916 5509.8321) (11866.4275 5511.3435)
      (11860.7481 5509.8321) (11856.6107 5505.6794)
    ))
    ; P3470 -- see feature_dimensions_mm.csv
    ("06_ORNAMENT" 1 (
      (11855.084 5125.9389) (11856.6107 5120.2748) (11860.7481 5116.1221) (11866.4275 5114.6107) (11872.0916 5116.1221)
      (11876.2443 5120.2748) (11877.7557 5125.9389) (11876.2443 5131.6183) (11872.0916 5135.7557) (11866.4275 5137.2824)
      (11860.7481 5135.7557) (11856.6107 5131.6183)
    ))
    ; P3471 -- see feature_dimensions_mm.csv
    ("06_ORNAMENT" 1 (
      (11855.084 4904.5954) (11856.6107 4898.916) (11860.7481 4894.7786) (11866.4275 4893.2519) (11872.0916 4894.7786)
      (11876.2443 4898.916) (11877.7557 4904.5954) (11876.2443 4910.2595) (11872.0916 4914.4122) (11866.4275 4915.9237)
      (11860.7481 4914.4122) (11856.6107 4910.2595)
    ))
    ; P3472 -- see feature_dimensions_mm.csv
    ("06_ORNAMENT" 1 (
      (11855.084 4530.5191) (11856.6107 4524.855) (11860.7481 4520.7023) (11866.4275 4519.1908) (11872.0916 4520.7023)
      (11876.2443 4524.855) (11877.7557 4530.5191) (11876.2443 4536.1985) (11872.0916 4540.3359) (11866.4275 4541.8626)
      (11860.7481 4540.3359) (11856.6107 4536.1985)
    ))
    ; P3473 -- see feature_dimensions_mm.csv
    ("06_ORNAMENT" 1 (
      (11855.084 4309.1756) (11856.6107 4303.4962) (11860.7481 4299.3588) (11866.4275 4297.8321) (11872.0916 4299.3588)
      (11876.2443 4303.4962) (11877.7557 4309.1756) (11876.2443 4314.8397) (11872.0916 4318.9924) (11866.4275 4320.5038)
      (11860.7481 4318.9924) (11856.6107 4314.8397)
    ))
    ; P3474 -- see feature_dimensions_mm.csv
    ("06_ORNAMENT" 1 (
      (11855.084 3935.0992) (11856.6107 3929.4351) (11860.7481 3925.2824) (11866.4275 3923.771) (11872.0916 3925.2824)
      (11876.2443 3929.4351) (11877.7557 3935.0992) (11876.2443 3940.7786) (11872.0916 3944.916) (11866.4275 3946.4427)
      (11860.7481 3944.916) (11856.6107 3940.7786)
    ))
    ; P3475 -- see feature_dimensions_mm.csv
    ("06_ORNAMENT" 1 (
      (11912.4275 5414.1985) (11913.9389 5408.5344) (11918.0916 5404.3817) (11923.7557 5402.855) (11929.4198 5404.3817)
      (11933.5725 5408.5344) (11935.0992 5414.1985) (11933.5725 5419.8626) (11929.4198 5424.0153) (11923.7557 5425.5267)
      (11918.0916 5424.0153) (11913.9389 5419.8626)
    ))
    ; P3476 -- see feature_dimensions_mm.csv
    ("06_ORNAMENT" 1 (
      (11912.4275 5211.7557) (11913.9389 5206.0916) (11918.0916 5201.9389) (11923.7557 5200.4275) (11929.4198 5201.9389)
      (11933.5725 5206.0916) (11935.0992 5211.7557) (11933.5725 5217.4198) (11929.4198 5221.5725) (11923.7557 5223.0992)
      (11918.0916 5221.5725) (11913.9389 5217.4198)
    ))
    ; P3477 -- see feature_dimensions_mm.csv
    ("06_ORNAMENT" 1 (
      (11912.4275 4818.7786) (11913.9389 4813.1145) (11918.0916 4808.9618) (11923.7557 4807.4351) (11929.4198 4808.9618)
      (11933.5725 4813.1145) (11935.0992 4818.7786) (11933.5725 4824.4427) (11929.4198 4828.5954) (11923.7557 4830.1069)
      (11918.0916 4828.5954) (11913.9389 4824.4427)
    ))
    ; P3478 -- see feature_dimensions_mm.csv
    ("06_ORNAMENT" 1 (
      (11912.4275 4616.3359) (11913.9389 4610.6718) (11918.0916 4606.5191) (11923.7557 4605.0076) (11929.4198 4606.5191)
      (11933.5725 4610.6718) (11935.0992 4616.3359) (11933.5725 4622.0) (11929.4198 4626.1527) (11923.7557 4627.6794)
      (11918.0916 4626.1527) (11913.9389 4622.0)
    ))
    ; P3479 -- see feature_dimensions_mm.csv
    ("06_ORNAMENT" 1 (
      (11912.4275 4223.3588) (11913.9389 4217.6947) (11918.0916 4213.542) (11923.7557 4212.0153) (11929.4198 4213.542)
      (11933.5725 4217.6947) (11935.0992 4223.3588) (11933.5725 4229.0229) (11929.4198 4233.1756) (11923.7557 4234.687)
      (11918.0916 4233.1756) (11913.9389 4229.0229)
    ))
    ; P3480 -- see feature_dimensions_mm.csv
    ("06_ORNAMENT" 1 (
      (11912.4275 4020.916) (11913.9389 4015.2519) (11918.0916 4011.0992) (11923.7557 4009.5878) (11929.4198 4011.0992)
      (11933.5725 4015.2519) (11935.0992 4020.916) (11933.5725 4026.5802) (11929.4198 4030.7328) (11923.7557 4032.2595)
      (11918.0916 4030.7328) (11913.9389 4026.5802)
    ))
    ; P3481 -- see feature_dimensions_mm.csv
    ("06_ORNAMENT" 1 (
      (11923.6641 6183.2061) (11924.9466 6167.0229) (11927.4046 6149.5115) (11931.0229 6130.9618) (11935.7252 6111.6489)
      (11941.4962 6091.8626) (11948.2748 6071.8931) (11956.0305 6052.0) (11964.687 6032.4885) (11974.2443 6013.6183)
      (11984.626 5995.6794) (11995.7863 5978.9618) (12007.7099 5963.7557) (12020.3206 5950.3053) (12033.5878 5938.9313)
      (12033.4198 5957.4198) (12031.313 5976.687) (12027.4656 5996.5038) (12022.0458 6016.6412) (12015.2672 6036.8397)
      (12007.2977 6056.9008) (11998.3359 6076.5496) (11988.5802 6095.5725) (11978.1985 6113.7252) (11967.3893 6130.7786)
      (11956.3511 6146.4885) (11945.2519 6160.6107) (11934.2901 6172.9313)
    ))
    ; P3482 -- see feature_dimensions_mm.csv
    ("06_ORNAMENT" 1 (
      (11932.5649 5312.9771) (11934.0763 5307.313) (11938.229 5303.1603) (11943.8931 5301.6336) (11949.5573 5303.1603)
      (11953.7099 5307.313) (11955.2366 5312.9771) (11953.7099 5318.6412) (11949.5573 5322.7939) (11943.8931 5324.3053)
      (11938.229 5322.7939) (11934.0763 5318.6412)
    ))
    ; P3483 -- see feature_dimensions_mm.csv
    ("06_ORNAMENT" 1 (
      (11932.5649 4717.5573) (11934.0763 4711.8931) (11938.229 4707.7405) (11943.8931 4706.2137) (11949.5573 4707.7405)
      (11953.7099 4711.8931) (11955.2366 4717.5573) (11953.7099 4723.2214) (11949.5573 4727.374) (11943.8931 4728.8855)
      (11938.229 4727.374) (11934.0763 4723.2214)
    ))
    ; P3484 -- see feature_dimensions_mm.csv
    ("06_ORNAMENT" 1 (
      (11932.5649 4122.1374) (11934.0763 4116.4733) (11938.229 4112.3206) (11943.8931 4110.7939) (11949.5573 4112.3206)
      (11953.7099 4116.4733) (11955.2366 4122.1374) (11953.7099 4127.8015) (11949.5573 4131.9542) (11943.8931 4133.4656)
      (11938.229 4131.9542) (11934.0763 4127.8015)
    ))
    ; P3485 -- see feature_dimensions_mm.csv
    ("06_ORNAMENT" 1 (
      (11962.5954 5504.0763) (11963.8168 5497.9389) (11967.2977 5492.7328) (11972.4885 5489.2672) (11978.626 5488.0458)
      (11984.7634 5489.2672) (11989.9542 5492.7328) (11993.4351 5497.9389) (11994.6565 5504.0763) (11993.4351 5510.2137)
      (11989.9542 5515.4046) (11984.7634 5518.8855) (11978.626 5520.1069) (11972.4885 5518.8855) (11967.2977 5515.4046)
      (11963.8168 5510.2137)
    ))
    ; P3486 -- see feature_dimensions_mm.csv
    ("06_ORNAMENT" 1 (
      (11962.5954 5427.7405) (11963.8168 5421.6031) (11967.2977 5416.3969) (11972.4885 5412.9313) (11978.626 5411.7099)
      (11984.7634 5412.9313) (11989.9542 5416.3969) (11993.4351 5421.6031) (11994.6565 5427.7405) (11993.4351 5433.8779)
      (11989.9542 5439.0687) (11984.7634 5442.5496) (11978.626 5443.771) (11972.4885 5442.5496) (11967.2977 5439.0687)
      (11963.8168 5433.8779)
    ))
    ; P3487 -- see feature_dimensions_mm.csv
    ("06_ORNAMENT" 1 (
      (11962.5954 5351.4046) (11963.8168 5345.2672) (11967.2977 5340.0611) (11972.4885 5336.5954) (11978.626 5335.374)
      (11984.7634 5336.5954) (11989.9542 5340.0611) (11993.4351 5345.2672) (11994.6565 5351.4046) (11993.4351 5357.542)
      (11989.9542 5362.7328) (11984.7634 5366.2137) (11978.626 5367.4351) (11972.4885 5366.2137) (11967.2977 5362.7328)
      (11963.8168 5357.542)
    ))
    ; P3488 -- see feature_dimensions_mm.csv
    ("06_ORNAMENT" 1 (
      (11962.5954 5275.0687) (11963.8168 5268.9313) (11967.2977 5263.7252) (11972.4885 5260.2595) (11978.626 5259.0382)
      (11984.7634 5260.2595) (11989.9542 5263.7252) (11993.4351 5268.9313) (11994.6565 5275.0687) (11993.4351 5281.2061)
      (11989.9542 5286.3969) (11984.7634 5289.8779) (11978.626 5291.0992) (11972.4885 5289.8779) (11967.2977 5286.3969)
      (11963.8168 5281.2061)
    ))
    ; P3489 -- see feature_dimensions_mm.csv
    ("06_ORNAMENT" 1 (
      (11962.5954 5198.7328) (11963.8168 5192.5954) (11967.2977 5187.3893) (11972.4885 5183.9237) (11978.626 5182.7023)
      (11984.7634 5183.9237) (11989.9542 5187.3893) (11993.4351 5192.5954) (11994.6565 5198.7328) (11993.4351 5204.8702)
      (11989.9542 5210.0611) (11984.7634 5213.542) (11978.626 5214.7634) (11972.4885 5213.542) (11967.2977 5210.0611)
      (11963.8168 5204.8702)
    ))
    ; P3490 -- see feature_dimensions_mm.csv
    ("06_ORNAMENT" 1 (
      (11962.5954 5122.3969) (11963.8168 5116.2595) (11967.2977 5111.0534) (11972.4885 5107.5878) (11978.626 5106.3664)
      (11984.7634 5107.5878) (11989.9542 5111.0534) (11993.4351 5116.2595) (11994.6565 5122.3969) (11993.4351 5128.5344)
      (11989.9542 5133.7252) (11984.7634 5137.2061) (11978.626 5138.4275) (11972.4885 5137.2061) (11967.2977 5133.7252)
      (11963.8168 5128.5344)
    ))
    ; P3491 -- see feature_dimensions_mm.csv
    ("06_ORNAMENT" 1 (
      (11962.5954 5046.0611) (11963.8168 5039.9237) (11967.2977 5034.7176) (11972.4885 5031.2519) (11978.626 5030.0305)
      (11984.7634 5031.2519) (11989.9542 5034.7176) (11993.4351 5039.9237) (11994.6565 5046.0611) (11993.4351 5052.1985)
      (11989.9542 5057.3893) (11984.7634 5060.8702) (11978.626 5062.0916) (11972.4885 5060.8702) (11967.2977 5057.3893)
      (11963.8168 5052.1985)
    ))
    ; P3492 -- see feature_dimensions_mm.csv
    ("06_ORNAMENT" 1 (
      (11962.5954 4969.7252) (11963.8168 4963.5878) (11967.2977 4958.3817) (11972.4885 4954.916) (11978.626 4953.6947)
      (11984.7634 4954.916) (11989.9542 4958.3817) (11993.4351 4963.5878) (11994.6565 4969.7252) (11993.4351 4975.8626)
      (11989.9542 4981.0534) (11984.7634 4984.5344) (11978.626 4985.7557) (11972.4885 4984.5344) (11967.2977 4981.0534)
      (11963.8168 4975.8626)
    ))
    ; P3493 -- see feature_dimensions_mm.csv
    ("06_ORNAMENT" 1 (
      (11962.5954 4893.3893) (11963.8168 4887.2519) (11967.2977 4882.0458) (11972.4885 4878.5802) (11978.626 4877.3588)
      (11984.7634 4878.5802) (11989.9542 4882.0458) (11993.4351 4887.2519) (11994.6565 4893.3893) (11993.4351 4899.5267)
      (11989.9542 4904.7176) (11984.7634 4908.1985) (11978.626 4909.4198) (11972.4885 4908.1985) (11967.2977 4904.7176)
      (11963.8168 4899.5267)
    ))
    ; P3494 -- see feature_dimensions_mm.csv
    ("06_ORNAMENT" 1 (
      (11962.5954 4817.0534) (11963.8168 4810.916) (11967.2977 4805.7099) (11972.4885 4802.2443) (11978.626 4801.0229)
      (11984.7634 4802.2443) (11989.9542 4805.7099) (11993.4351 4810.916) (11994.6565 4817.0534) (11993.4351 4823.1908)
      (11989.9542 4828.3817) (11984.7634 4831.8626) (11978.626 4833.084) (11972.4885 4831.8626) (11967.2977 4828.3817)
      (11963.8168 4823.1908)
    ))
    ; P3495 -- see feature_dimensions_mm.csv
    ("06_ORNAMENT" 1 (
      (11962.5954 4664.3817) (11963.8168 4658.2443) (11967.2977 4653.0382) (11972.4885 4649.5725) (11978.626 4648.3511)
      (11984.7634 4649.5725) (11989.9542 4653.0382) (11993.4351 4658.2443) (11994.6565 4664.3817) (11993.4351 4670.5191)
      (11989.9542 4675.7099) (11984.7634 4679.1908) (11978.626 4680.4122) (11972.4885 4679.1908) (11967.2977 4675.7099)
      (11963.8168 4670.5191)
    ))
    ; P3496 -- see feature_dimensions_mm.csv
    ("06_ORNAMENT" 1 (
      (11962.5954 4588.0458) (11963.8168 4581.9084) (11967.2977 4576.7023) (11972.4885 4573.2366) (11978.626 4572.0153)
      (11984.7634 4573.2366) (11989.9542 4576.7023) (11993.4351 4581.9084) (11994.6565 4588.0458) (11993.4351 4594.1832)
      (11989.9542 4599.374) (11984.7634 4602.855) (11978.626 4604.0763) (11972.4885 4602.855) (11967.2977 4599.374)
      (11963.8168 4594.1832)
    ))
    ; P3497 -- see feature_dimensions_mm.csv
    ("06_ORNAMENT" 1 (
      (11962.5954 4511.7099) (11963.8168 4505.5725) (11967.2977 4500.3664) (11972.4885 4496.9008) (11978.626 4495.6794)
      (11984.7634 4496.9008) (11989.9542 4500.3664) (11993.4351 4505.5725) (11994.6565 4511.7099) (11993.4351 4517.8473)
      (11989.9542 4523.0382) (11984.7634 4526.5191) (11978.626 4527.7405) (11972.4885 4526.5191) (11967.2977 4523.0382)
      (11963.8168 4517.8473)
    ))
    ; P3498 -- see feature_dimensions_mm.csv
    ("06_ORNAMENT" 1 (
      (11962.5954 4359.0382) (11963.8168 4352.9008) (11967.2977 4347.6947) (11972.4885 4344.229) (11978.626 4343.0076)
      (11984.7634 4344.229) (11989.9542 4347.6947) (11993.4351 4352.9008) (11994.6565 4359.0382) (11993.4351 4365.1756)
      (11989.9542 4370.3664) (11984.7634 4373.8473) (11978.626 4375.0687) (11972.4885 4373.8473) (11967.2977 4370.3664)
      (11963.8168 4365.1756)
    ))
    ; P3499 -- see feature_dimensions_mm.csv
    ("06_ORNAMENT" 1 (
      (11962.5954 4282.7023) (11963.8168 4276.5649) (11967.2977 4271.3588) (11972.4885 4267.8931) (11978.626 4266.6718)
      (11984.7634 4267.8931) (11989.9542 4271.3588) (11993.4351 4276.5649) (11994.6565 4282.7023) (11993.4351 4288.8397)
      (11989.9542 4294.0305) (11984.7634 4297.5115) (11978.626 4298.7328) (11972.4885 4297.5115) (11967.2977 4294.0305)
      (11963.8168 4288.8397)
    ))
    ; P3500 -- see feature_dimensions_mm.csv
    ("06_ORNAMENT" 1 (
      (11962.5954 4206.3664) (11963.8168 4200.229) (11967.2977 4195.0229) (11972.4885 4191.5573) (11978.626 4190.3359)
      (11984.7634 4191.5573) (11989.9542 4195.0229) (11993.4351 4200.229) (11994.6565 4206.3664) (11993.4351 4212.5038)
      (11989.9542 4217.6947) (11984.7634 4221.1756) (11978.626 4222.3969) (11972.4885 4221.1756) (11967.2977 4217.6947)
      (11963.8168 4212.5038)
    ))
    ; P3501 -- see feature_dimensions_mm.csv
    ("06_ORNAMENT" 1 (
      (11962.5954 4053.6947) (11963.8168 4047.5573) (11967.2977 4042.3511) (11972.4885 4038.8855) (11978.626 4037.6641)
      (11984.7634 4038.8855) (11989.9542 4042.3511) (11993.4351 4047.5573) (11994.6565 4053.6947) (11993.4351 4059.8321)
      (11989.9542 4065.0229) (11984.7634 4068.5038) (11978.626 4069.7252) (11972.4885 4068.5038) (11967.2977 4065.0229)
      (11963.8168 4059.8321)
    ))
    ; P3502 -- see feature_dimensions_mm.csv
    ("06_ORNAMENT" 1 (
      (11962.5954 3977.3588) (11963.8168 3971.2214) (11967.2977 3966.0153) (11972.4885 3962.5496) (11978.626 3961.3282)
      (11984.7634 3962.5496) (11989.9542 3966.0153) (11993.4351 3971.2214) (11994.6565 3977.3588) (11993.4351 3983.4962)
      (11989.9542 3988.687) (11984.7634 3992.1679) (11978.626 3993.3893) (11972.4885 3992.1679) (11967.2977 3988.687)
      (11963.8168 3983.4962)
    ))
    ; P3503 -- see feature_dimensions_mm.csv
    ("06_ORNAMENT" 1 (
      (11962.5954 3901.0229) (11963.8168 3894.8855) (11967.2977 3889.6794) (11972.4885 3886.2137) (11978.626 3884.9924)
      (11984.7634 3886.2137) (11989.9542 3889.6794) (11993.4351 3894.8855) (11994.6565 3901.0229) (11993.4351 3907.1603)
      (11989.9542 3912.3511) (11984.7634 3915.8321) (11978.626 3917.0534) (11972.4885 3915.8321) (11967.2977 3912.3511)
      (11963.8168 3907.1603)
    ))
    ; P3504 -- see feature_dimensions_mm.csv
    ("06_ORNAMENT" 1 (
      (12036.626 6048.9771) (12037.6031 6028.5191) (12039.7099 6008.5496) (12043.0229 5989.3282) (12047.6489 5971.145)
      (12053.6336 5954.2595) (12061.0687 5938.9313) (12068.5038 5955.3282) (12074.4885 5973.1908) (12079.1145 5992.2443)
      (12082.4275 6012.1832) (12084.5344 6032.7328) (12085.5115 6053.6183) (12085.4046 6074.5344) (12084.3053 6095.2366)
      (12082.2901 6115.4046) (12079.4351 6134.7634) (12075.8015 6153.0382) (12071.4809 6169.9237) (12066.5496 6185.1756)
      (12061.0687 6198.4733) (12055.5878 6183.6641) (12050.6565 6167.2061) (12046.3359 6149.374) (12042.7023 6130.4427)
      (12039.8473 6110.6718) (12037.8321 6090.3206) (12036.7328 6069.6794)
    ))
    ; P3505 -- see feature_dimensions_mm.csv
    ("06_ORNAMENT" 1 (
      (12036.6412 7374.0458) (12038.0 7371.5267) (12041.7099 7369.4809) (12046.7481 7368.1527) (12051.8015 7367.4656)
      (12055.5878 7367.0076) (12057.2672 7366.1527) (12056.6718 7364.3511) (12054.3359 7361.3435) (12051.2519 7357.2824)
      (12048.626 7352.7786) (12047.4504 7348.7176) (12048.2748 7345.9847) (12051.0076 7345.1603) (12055.0687 7346.3359)
      (12059.5725 7348.9618) (12063.6336 7352.0458) (12066.6412 7354.3817) (12068.4427 7354.9771) (12069.2977 7353.2977)
      (12069.7557 7349.5115) (12070.458 7344.458) (12071.771 7339.4198) (12073.8168 7335.7099) (12076.3359 7334.3511)
      (12078.855 7335.7099) (12080.9008 7339.4198) (12082.229 7344.458) (12082.916 7349.5115) (12083.374 7353.2977)
      (12084.229 7354.9771) (12086.0305 7354.3817) (12089.0382 7352.0458) (12093.0992 7348.9618) (12097.6031 7346.3359)
      (12101.6641 7345.1603) (12104.3969 7345.9847) (12105.2214 7348.7176) (12104.0458 7352.7786) (12101.4198 7357.2824)
      (12098.3359 7361.3435) (12096.0 7364.3511) (12095.4046 7366.1527) (12097.084 7367.0076) (12100.8702 7367.4656)
      (12105.9237 7368.1527) (12110.9618 7369.4809) (12114.6718 7371.5267) (12116.0305 7374.0458) (12114.6718 7376.5649)
      (12110.9618 7378.6107) (12105.9237 7379.9237) (12100.8702 7380.626) (12097.084 7381.084) (12095.4046 7381.9389)
      (12096.0 7383.7405) (12098.3359 7386.7481) (12101.4198 7390.8092) (12104.0458 7395.313) (12105.2214 7399.374)
      (12104.3969 7402.1069) (12101.6641 7402.9313) (12097.6031 7401.7557) (12093.0992 7399.1298) (12089.0382 7396.0458)
      (12086.0305 7393.7099) (12084.229 7393.1145) (12083.374 7394.7939) (12082.916 7398.5802) (12082.229 7403.6336)
      (12080.9008 7408.6718) (12078.855 7412.3817) (12076.3359 7413.7405) (12073.8168 7412.3817) (12071.771 7408.6718)
      (12070.458 7403.6336) (12069.7557 7398.5802) (12069.2977 7394.7939) (12068.4427 7393.1145) (12066.6412 7393.7099)
      (12063.6336 7396.0458) (12059.5725 7399.1298) (12055.0687 7401.7557) (12051.0076 7402.9313) (12048.2748 7402.1069)
      (12047.4504 7399.374) (12048.626 7395.313) (12051.2519 7390.8092) (12054.3359 7386.7481) (12056.6718 7383.7405)
      (12057.2672 7381.9389) (12055.5878 7381.084) (12051.8015 7380.626) (12046.7481 7379.9237) (12041.7099 7378.6107)
      (12038.0 7376.5649)
    ))
    ; P3506 -- see feature_dimensions_mm.csv
    ("06_ORNAMENT" 1 (
      (12036.6412 7206.1069) (12038.0 7203.5878) (12041.7099 7201.542) (12046.7481 7200.2137) (12051.8015 7199.5267)
      (12055.5878 7199.0687) (12057.2672 7198.2137) (12056.6718 7196.4122) (12054.3359 7193.4046) (12051.2519 7189.3435)
      (12048.626 7184.8397) (12047.4504 7180.7786) (12048.2748 7178.0458) (12051.0076 7177.2214) (12055.0687 7178.3969)
      (12059.5725 7181.0229) (12063.6336 7184.1069) (12066.6412 7186.4427) (12068.4427 7187.0382) (12069.2977 7185.3588)
      (12069.7557 7181.5725) (12070.458 7176.5191) (12071.771 7171.4809) (12073.8168 7167.771) (12076.3359 7166.4122)
      (12078.855 7167.771) (12080.9008 7171.4809) (12082.229 7176.5191) (12082.916 7181.5725) (12083.374 7185.3588)
      (12084.229 7187.0382) (12086.0305 7186.4427) (12089.0382 7184.1069) (12093.0992 7181.0229) (12097.6031 7178.3969)
      (12101.6641 7177.2214) (12104.3969 7178.0458) (12105.2214 7180.7786) (12104.0458 7184.8397) (12101.4198 7189.3435)
      (12098.3359 7193.4046) (12096.0 7196.4122) (12095.4046 7198.2137) (12097.084 7199.0687) (12100.8702 7199.5267)
      (12105.9237 7200.2137) (12110.9618 7201.542) (12114.6718 7203.5878) (12116.0305 7206.1069) (12114.6718 7208.626)
      (12110.9618 7210.6718) (12105.9237 7211.9847) (12100.8702 7212.687) (12097.084 7213.145) (12095.4046 7214.0)
      (12096.0 7215.8015) (12098.3359 7218.8092) (12101.4198 7222.8702) (12104.0458 7227.374) (12105.2214 7231.4351)
      (12104.3969 7234.1679) (12101.6641 7234.9924) (12097.6031 7233.8168) (12093.0992 7231.1908) (12089.0382 7228.1069)
      (12086.0305 7225.771) (12084.229 7225.1756) (12083.374 7226.855) (12082.916 7230.6412) (12082.229 7235.6947)
      (12080.9008 7240.7328) (12078.855 7244.4427) (12076.3359 7245.8015) (12073.8168 7244.4427) (12071.771 7240.7328)
      (12070.458 7235.6947) (12069.7557 7230.6412) (12069.2977 7226.855) (12068.4427 7225.1756) (12066.6412 7225.771)
      (12063.6336 7228.1069) (12059.5725 7231.1908) (12055.0687 7233.8168) (12051.0076 7234.9924) (12048.2748 7234.1679)
      (12047.4504 7231.4351) (12048.626 7227.374) (12051.2519 7222.8702) (12054.3359 7218.8092) (12056.6718 7215.8015)
      (12057.2672 7214.0) (12055.5878 7213.145) (12051.8015 7212.687) (12046.7481 7211.9847) (12041.7099 7210.6718)
      (12038.0 7208.626)
    ))
    ; P3507 -- see feature_dimensions_mm.csv
    ("06_ORNAMENT" 1 (
      (12067.2061 7374.0458) (12067.9084 7370.5496) (12069.8779 7367.5878) (12072.8397 7365.6183) (12076.3359 7364.916)
      (12079.8321 7365.6183) (12082.7939 7367.5878) (12084.7634 7370.5496) (12085.4656 7374.0458) (12084.7634 7377.542)
      (12082.7939 7380.5038) (12079.8321 7382.4733) (12076.3359 7383.1756) (12072.8397 7382.4733) (12069.8779 7380.5038)
      (12067.9084 7377.542)
    ))
    ; P3508 -- see feature_dimensions_mm.csv
    ("06_ORNAMENT" 1 (
      (12067.2061 7206.1069) (12067.9084 7202.6107) (12069.8779 7199.6489) (12072.8397 7197.6794) (12076.3359 7196.9771)
      (12079.8321 7197.6794) (12082.7939 7199.6489) (12084.7634 7202.6107) (12085.4656 7206.1069) (12084.7634 7209.6031)
      (12082.7939 7212.5649) (12079.8321 7214.5344) (12076.3359 7215.2366) (12072.8397 7214.5344) (12069.8779 7212.5649)
      (12067.9084 7209.6031)
    ))
    ; P3509 -- see feature_dimensions_mm.csv
    ("06_ORNAMENT" 1 (
      (12088.2595 5956.4122) (12088.5496 5938.9313) (12102.2748 5951.313) (12115.2977 5965.6641) (12127.5725 5981.6947)
      (12139.0534 5999.0992) (12149.6794 6017.5878) (12159.4046 6036.8397) (12168.1679 6056.5802) (12175.9389 6076.5038)
      (12182.6412 6096.3053) (12188.229 6115.7099) (12192.6718 6134.3969) (12195.8779 6152.0763) (12197.8321 6168.4427)
      (12198.4733 6183.2061) (12187.2061 6171.5115) (12175.7405 6158.0458) (12164.2443 6143.0534) (12152.916 6126.7176)
      (12141.9389 6109.2824) (12131.4809 6090.9618) (12121.7405 6071.9695) (12112.8702 6052.5344) (12105.084 6032.8855)
      (12098.5496 6013.2214) (12093.4504 5993.771) (12089.9542 5974.7634)
    ))
    ; P3510 -- see feature_dimensions_mm.csv
    ("06_ORNAMENT" 1 (
      (12116.0305 5938.9313) (12134.9008 5945.9542) (12154.0458 5955.1756) (12173.2672 5966.3053) (12192.3969 5979.084)
      (12211.2214 5993.2366) (12229.542 6008.4885) (12247.2061 6024.5802) (12264.0 6041.2061) (12279.7252 6058.1221)
      (12294.2137 6075.0534) (12307.2672 6091.7252) (12318.687 6107.8473) (12328.2901 6123.1603) (12335.8779 6137.4046)
      (12319.6641 6130.1374) (12302.4122 6121.2214) (12284.4275 6110.7939) (12265.9542 6099.0076) (12247.2824 6086.0153)
      (12228.7023 6071.9542) (12210.4733 6056.9771) (12192.8702 6041.2214) (12176.1832 6024.855) (12160.687 6008.0305)
      (12146.6412 5990.8702) (12134.3359 5973.5267) (12124.0305 5956.1679)
    ))
    ; P3511 -- see feature_dimensions_mm.csv
    ("06_ORNAMENT" 1 (
      (12127.4809 5504.0763) (12128.7023 5497.9389) (12132.1832 5492.7328) (12137.374 5489.2672) (12143.5115 5488.0458)
      (12149.6489 5489.2672) (12154.8397 5492.7328) (12158.3206 5497.9389) (12159.542 5504.0763) (12158.3206 5510.2137)
      (12154.8397 5515.4046) (12149.6489 5518.8855) (12143.5115 5520.1069) (12137.374 5518.8855) (12132.1832 5515.4046)
      (12128.7023 5510.2137)
    ))
    ; P3512 -- see feature_dimensions_mm.csv
    ("06_ORNAMENT" 1 (
      (12127.4809 5427.7405) (12128.7023 5421.6031) (12132.1832 5416.3969) (12137.374 5412.9313) (12143.5115 5411.7099)
      (12149.6489 5412.9313) (12154.8397 5416.3969) (12158.3206 5421.6031) (12159.542 5427.7405) (12158.3206 5433.8779)
      (12154.8397 5439.0687) (12149.6489 5442.5496) (12143.5115 5443.771) (12137.374 5442.5496) (12132.1832 5439.0687)
      (12128.7023 5433.8779)
    ))
    ; P3513 -- see feature_dimensions_mm.csv
    ("06_ORNAMENT" 1 (
      (12127.4809 5351.4046) (12128.7023 5345.2672) (12132.1832 5340.0611) (12137.374 5336.5954) (12143.5115 5335.374)
      (12149.6489 5336.5954) (12154.8397 5340.0611) (12158.3206 5345.2672) (12159.542 5351.4046) (12158.3206 5357.542)
      (12154.8397 5362.7328) (12149.6489 5366.2137) (12143.5115 5367.4351) (12137.374 5366.2137) (12132.1832 5362.7328)
      (12128.7023 5357.542)
    ))
    ; P3514 -- see feature_dimensions_mm.csv
    ("06_ORNAMENT" 1 (
      (12127.4809 5275.0687) (12128.7023 5268.9313) (12132.1832 5263.7252) (12137.374 5260.2595) (12143.5115 5259.0382)
      (12149.6489 5260.2595) (12154.8397 5263.7252) (12158.3206 5268.9313) (12159.542 5275.0687) (12158.3206 5281.2061)
      (12154.8397 5286.3969) (12149.6489 5289.8779) (12143.5115 5291.0992) (12137.374 5289.8779) (12132.1832 5286.3969)
      (12128.7023 5281.2061)
    ))
    ; P3515 -- see feature_dimensions_mm.csv
    ("06_ORNAMENT" 1 (
      (12127.4809 5198.7328) (12128.7023 5192.5954) (12132.1832 5187.3893) (12137.374 5183.9237) (12143.5115 5182.7023)
      (12149.6489 5183.9237) (12154.8397 5187.3893) (12158.3206 5192.5954) (12159.542 5198.7328) (12158.3206 5204.8702)
      (12154.8397 5210.0611) (12149.6489 5213.542) (12143.5115 5214.7634) (12137.374 5213.542) (12132.1832 5210.0611)
      (12128.7023 5204.8702)
    ))
    ; P3516 -- see feature_dimensions_mm.csv
    ("06_ORNAMENT" 1 (
      (12127.4809 5122.3969) (12128.7023 5116.2595) (12132.1832 5111.0534) (12137.374 5107.5878) (12143.5115 5106.3664)
      (12149.6489 5107.5878) (12154.8397 5111.0534) (12158.3206 5116.2595) (12159.542 5122.3969) (12158.3206 5128.5344)
      (12154.8397 5133.7252) (12149.6489 5137.2061) (12143.5115 5138.4275) (12137.374 5137.2061) (12132.1832 5133.7252)
      (12128.7023 5128.5344)
    ))
    ; P3517 -- see feature_dimensions_mm.csv
    ("06_ORNAMENT" 1 (
      (12127.4809 5046.0611) (12128.7023 5039.9237) (12132.1832 5034.7176) (12137.374 5031.2519) (12143.5115 5030.0305)
      (12149.6489 5031.2519) (12154.8397 5034.7176) (12158.3206 5039.9237) (12159.542 5046.0611) (12158.3206 5052.1985)
      (12154.8397 5057.3893) (12149.6489 5060.8702) (12143.5115 5062.0916) (12137.374 5060.8702) (12132.1832 5057.3893)
      (12128.7023 5052.1985)
    ))
    ; P3518 -- see feature_dimensions_mm.csv
    ("06_ORNAMENT" 1 (
      (12127.4809 4969.7252) (12128.7023 4963.5878) (12132.1832 4958.3817) (12137.374 4954.916) (12143.5115 4953.6947)
      (12149.6489 4954.916) (12154.8397 4958.3817) (12158.3206 4963.5878) (12159.542 4969.7252) (12158.3206 4975.8626)
      (12154.8397 4981.0534) (12149.6489 4984.5344) (12143.5115 4985.7557) (12137.374 4984.5344) (12132.1832 4981.0534)
      (12128.7023 4975.8626)
    ))
    ; P3519 -- see feature_dimensions_mm.csv
    ("06_ORNAMENT" 1 (
      (12127.4809 4893.3893) (12128.7023 4887.2519) (12132.1832 4882.0458) (12137.374 4878.5802) (12143.5115 4877.3588)
      (12149.6489 4878.5802) (12154.8397 4882.0458) (12158.3206 4887.2519) (12159.542 4893.3893) (12158.3206 4899.5267)
      (12154.8397 4904.7176) (12149.6489 4908.1985) (12143.5115 4909.4198) (12137.374 4908.1985) (12132.1832 4904.7176)
      (12128.7023 4899.5267)
    ))
    ; P3520 -- see feature_dimensions_mm.csv
    ("06_ORNAMENT" 1 (
      (12127.4809 4817.0534) (12128.7023 4810.916) (12132.1832 4805.7099) (12137.374 4802.2443) (12143.5115 4801.0229)
      (12149.6489 4802.2443) (12154.8397 4805.7099) (12158.3206 4810.916) (12159.542 4817.0534) (12158.3206 4823.1908)
      (12154.8397 4828.3817) (12149.6489 4831.8626) (12143.5115 4833.084) (12137.374 4831.8626) (12132.1832 4828.3817)
      (12128.7023 4823.1908)
    ))
    ; P3521 -- see feature_dimensions_mm.csv
    ("06_ORNAMENT" 1 (
      (12127.4809 4664.3817) (12128.7023 4658.2443) (12132.1832 4653.0382) (12137.374 4649.5725) (12143.5115 4648.3511)
      (12149.6489 4649.5725) (12154.8397 4653.0382) (12158.3206 4658.2443) (12159.542 4664.3817) (12158.3206 4670.5191)
      (12154.8397 4675.7099) (12149.6489 4679.1908) (12143.5115 4680.4122) (12137.374 4679.1908) (12132.1832 4675.7099)
      (12128.7023 4670.5191)
    ))
    ; P3522 -- see feature_dimensions_mm.csv
    ("06_ORNAMENT" 1 (
      (12127.4809 4588.0458) (12128.7023 4581.9084) (12132.1832 4576.7023) (12137.374 4573.2366) (12143.5115 4572.0153)
      (12149.6489 4573.2366) (12154.8397 4576.7023) (12158.3206 4581.9084) (12159.542 4588.0458) (12158.3206 4594.1832)
      (12154.8397 4599.374) (12149.6489 4602.855) (12143.5115 4604.0763) (12137.374 4602.855) (12132.1832 4599.374)
      (12128.7023 4594.1832)
    ))
    ; P3523 -- see feature_dimensions_mm.csv
    ("06_ORNAMENT" 1 (
      (12127.4809 4511.7099) (12128.7023 4505.5725) (12132.1832 4500.3664) (12137.374 4496.9008) (12143.5115 4495.6794)
      (12149.6489 4496.9008) (12154.8397 4500.3664) (12158.3206 4505.5725) (12159.542 4511.7099) (12158.3206 4517.8473)
      (12154.8397 4523.0382) (12149.6489 4526.5191) (12143.5115 4527.7405) (12137.374 4526.5191) (12132.1832 4523.0382)
      (12128.7023 4517.8473)
    ))
    ; P3524 -- see feature_dimensions_mm.csv
    ("06_ORNAMENT" 1 (
      (12127.4809 4359.0382) (12128.7023 4352.9008) (12132.1832 4347.6947) (12137.374 4344.229) (12143.5115 4343.0076)
      (12149.6489 4344.229) (12154.8397 4347.6947) (12158.3206 4352.9008) (12159.542 4359.0382) (12158.3206 4365.1756)
      (12154.8397 4370.3664) (12149.6489 4373.8473) (12143.5115 4375.0687) (12137.374 4373.8473) (12132.1832 4370.3664)
      (12128.7023 4365.1756)
    ))
    ; P3525 -- see feature_dimensions_mm.csv
    ("06_ORNAMENT" 1 (
      (12127.4809 4282.7023) (12128.7023 4276.5649) (12132.1832 4271.3588) (12137.374 4267.8931) (12143.5115 4266.6718)
      (12149.6489 4267.8931) (12154.8397 4271.3588) (12158.3206 4276.5649) (12159.542 4282.7023) (12158.3206 4288.8397)
      (12154.8397 4294.0305) (12149.6489 4297.5115) (12143.5115 4298.7328) (12137.374 4297.5115) (12132.1832 4294.0305)
      (12128.7023 4288.8397)
    ))
    ; P3526 -- see feature_dimensions_mm.csv
    ("06_ORNAMENT" 1 (
      (12127.4809 4206.3664) (12128.7023 4200.229) (12132.1832 4195.0229) (12137.374 4191.5573) (12143.5115 4190.3359)
      (12149.6489 4191.5573) (12154.8397 4195.0229) (12158.3206 4200.229) (12159.542 4206.3664) (12158.3206 4212.5038)
      (12154.8397 4217.6947) (12149.6489 4221.1756) (12143.5115 4222.3969) (12137.374 4221.1756) (12132.1832 4217.6947)
      (12128.7023 4212.5038)
    ))
    ; P3527 -- see feature_dimensions_mm.csv
    ("06_ORNAMENT" 1 (
      (12127.4809 4053.6947) (12128.7023 4047.5573) (12132.1832 4042.3511) (12137.374 4038.8855) (12143.5115 4037.6641)
      (12149.6489 4038.8855) (12154.8397 4042.3511) (12158.3206 4047.5573) (12159.542 4053.6947) (12158.3206 4059.8321)
      (12154.8397 4065.0229) (12149.6489 4068.5038) (12143.5115 4069.7252) (12137.374 4068.5038) (12132.1832 4065.0229)
      (12128.7023 4059.8321)
    ))
    ; P3528 -- see feature_dimensions_mm.csv
    ("06_ORNAMENT" 1 (
      (12127.4809 3977.3588) (12128.7023 3971.2214) (12132.1832 3966.0153) (12137.374 3962.5496) (12143.5115 3961.3282)
      (12149.6489 3962.5496) (12154.8397 3966.0153) (12158.3206 3971.2214) (12159.542 3977.3588) (12158.3206 3983.4962)
      (12154.8397 3988.687) (12149.6489 3992.1679) (12143.5115 3993.3893) (12137.374 3992.1679) (12132.1832 3988.687)
      (12128.7023 3983.4962)
    ))
    ; P3529 -- see feature_dimensions_mm.csv
    ("06_ORNAMENT" 1 (
      (12127.4809 3901.0229) (12128.7023 3894.8855) (12132.1832 3889.6794) (12137.374 3886.2137) (12143.5115 3884.9924)
      (12149.6489 3886.2137) (12154.8397 3889.6794) (12158.3206 3894.8855) (12159.542 3901.0229) (12158.3206 3907.1603)
      (12154.8397 3912.3511) (12149.6489 3915.8321) (12143.5115 3917.0534) (12137.374 3915.8321) (12132.1832 3912.3511)
      (12128.7023 3907.1603)
    ))
    ; P3530 -- see feature_dimensions_mm.csv
    ("06_ORNAMENT" 1 (
      (12166.916 5312.9771) (12168.4275 5307.313) (12172.5802 5303.1603) (12178.2443 5301.6336) (12183.9084 5303.1603)
      (12188.0611 5307.313) (12189.5878 5312.9771) (12188.0611 5318.6412) (12183.9084 5322.7939) (12178.2443 5324.3053)
      (12172.5802 5322.7939) (12168.4275 5318.6412)
    ))
    ; P3531 -- see feature_dimensions_mm.csv
    ("06_ORNAMENT" 1 (
      (12166.916 4717.5573) (12168.4275 4711.8931) (12172.5802 4707.7405) (12178.2443 4706.2137) (12183.9084 4707.7405)
      (12188.0611 4711.8931) (12189.5878 4717.5573) (12188.0611 4723.2214) (12183.9084 4727.374) (12178.2443 4728.8855)
      (12172.5802 4727.374) (12168.4275 4723.2214)
    ))
    ; P3532 -- see feature_dimensions_mm.csv
    ("06_ORNAMENT" 1 (
      (12166.916 4122.1374) (12168.4275 4116.4733) (12172.5802 4112.3206) (12178.2443 4110.7939) (12183.9084 4112.3206)
      (12188.0611 4116.4733) (12189.5878 4122.1374) (12188.0611 4127.8015) (12183.9084 4131.9542) (12178.2443 4133.4656)
      (12172.5802 4131.9542) (12168.4275 4127.8015)
    ))
    ; P3533 -- see feature_dimensions_mm.csv
    ("06_ORNAMENT" 1 (
      (12187.0382 5414.1985) (12188.5649 5408.5344) (12192.7176 5404.3817) (12198.3817 5402.855) (12204.0458 5404.3817)
      (12208.1985 5408.5344) (12209.7099 5414.1985) (12208.1985 5419.8626) (12204.0458 5424.0153) (12198.3817 5425.5267)
      (12192.7176 5424.0153) (12188.5649 5419.8626)
    ))
    ; P3534 -- see feature_dimensions_mm.csv
    ("06_ORNAMENT" 1 (
      (12187.0382 5211.7557) (12188.5649 5206.0916) (12192.7176 5201.9389) (12198.3817 5200.4275) (12204.0458 5201.9389)
      (12208.1985 5206.0916) (12209.7099 5211.7557) (12208.1985 5217.4198) (12204.0458 5221.5725) (12198.3817 5223.0992)
      (12192.7176 5221.5725) (12188.5649 5217.4198)
    ))
    ; P3535 -- see feature_dimensions_mm.csv
    ("06_ORNAMENT" 1 (
      (12187.0382 4818.7786) (12188.5649 4813.1145) (12192.7176 4808.9618) (12198.3817 4807.4351) (12204.0458 4808.9618)
      (12208.1985 4813.1145) (12209.7099 4818.7786) (12208.1985 4824.4427) (12204.0458 4828.5954) (12198.3817 4830.1069)
      (12192.7176 4828.5954) (12188.5649 4824.4427)
    ))
    ; P3536 -- see feature_dimensions_mm.csv
    ("06_ORNAMENT" 1 (
      (12187.0382 4616.3359) (12188.5649 4610.6718) (12192.7176 4606.5191) (12198.3817 4605.0076) (12204.0458 4606.5191)
      (12208.1985 4610.6718) (12209.7099 4616.3359) (12208.1985 4622.0) (12204.0458 4626.1527) (12198.3817 4627.6794)
      (12192.7176 4626.1527) (12188.5649 4622.0)
    ))
    ; P3537 -- see feature_dimensions_mm.csv
    ("06_ORNAMENT" 1 (
      (12187.0382 4223.3588) (12188.5649 4217.6947) (12192.7176 4213.542) (12198.3817 4212.0153) (12204.0458 4213.542)
      (12208.1985 4217.6947) (12209.7099 4223.3588) (12208.1985 4229.0229) (12204.0458 4233.1756) (12198.3817 4234.687)
      (12192.7176 4233.1756) (12188.5649 4229.0229)
    ))
    ; P3538 -- see feature_dimensions_mm.csv
    ("06_ORNAMENT" 1 (
      (12187.0382 4020.916) (12188.5649 4015.2519) (12192.7176 4011.0992) (12198.3817 4009.5878) (12204.0458 4011.0992)
      (12208.1985 4015.2519) (12209.7099 4020.916) (12208.1985 4026.5802) (12204.0458 4030.7328) (12198.3817 4032.2595)
      (12192.7176 4030.7328) (12188.5649 4026.5802)
    ))
    ; P3539 -- see feature_dimensions_mm.csv
    ("06_ORNAMENT" 1 (
      (12193.3588 4122.1374) (12193.7252 4118.3969) (12194.8397 4114.7481) (12196.3206 4111.9084) (12196.8244 4100.626)
      (12199.6336 4079.2672) (12204.2901 4058.2443) (12210.7634 4037.7099) (12219.0076 4017.8015) (12228.9466 3998.7023)
      (12240.5191 3980.5344) (12253.6336 3963.4504) (12261.2672 3955.1298) (12262.2137 3952.0611) (12264.0153 3948.7023)
      (12266.3969 3945.7863) (12269.313 3943.4046) (12272.6718 3941.6031) (12275.7405 3940.6565) (12284.0611 3933.0229)
      (12301.145 3919.9084) (12319.313 3908.3359) (12338.4122 3898.3969) (12358.3206 3890.1527) (12378.855 3883.6794)
      (12399.8779 3879.0229) (12421.2366 3876.2137) (12432.5191 3875.7099) (12435.3588 3874.229) (12439.0076 3873.1145)
      (12442.7481 3872.7481) (12446.4885 3873.1145) (12450.1374 3874.229) (12452.9771 3875.7099) (12464.2595 3876.2137)
      (12485.6183 3879.0229) (12506.6412 3883.6794) (12527.1756 3890.1527) (12547.084 3898.3969) (12566.1832 3908.3359)
      (12584.3511 3919.9084) (12601.4351 3933.0229) (12609.7557 3940.6565) (12612.8244 3941.6031) (12616.1832 3943.4046)
      (12619.0992 3945.7863) (12621.4809 3948.7023) (12623.2824 3952.0611) (12624.229 3955.1298) (12631.8626 3963.4504)
      (12644.9771 3980.5344) (12656.5496 3998.7023) (12666.4885 4017.8015) (12674.7328 4037.7099) (12681.2061 4058.2443)
      (12685.8626 4079.2672) (12688.6718 4100.626) (12689.1756 4111.9084) (12690.6565 4114.7481) (12691.771 4118.3969)
      (12692.1374 4122.1374) (12691.771 4125.8779) (12690.6565 4129.5267) (12689.1756 4132.3664) (12688.6718 4143.6489)
      (12685.8626 4165.0076) (12681.2061 4186.0305) (12674.7328 4206.5649) (12666.4885 4226.4733) (12656.5496 4245.5725)
      (12644.9771 4263.7405) (12631.8626 4280.8244) (12624.229 4289.145) (12623.2824 4292.2137) (12621.4809 4295.5725)
      (12619.0992 4298.4885) (12616.1832 4300.8702) (12612.8244 4302.6718) (12609.7557 4303.6183) (12601.4351 4311.2519)
      (12584.3511 4324.3664) (12566.1832 4335.9389) (12547.084 4345.8779) (12527.1756 4354.1221) (12506.6412 4360.5954)
      (12485.6183 4365.2519) (12464.2595 4368.0611) (12452.9771 4368.5649) (12450.1374 4370.0458) (12446.4885 4371.1603)
      (12442.7481 4371.5267) (12439.0076 4371.1603) (12435.3588 4370.0458) (12432.5191 4368.5649) (12421.2366 4368.0611)
      (12399.8779 4365.2519) (12378.855 4360.5954) (12358.3206 4354.1221) (12338.4122 4345.8779) (12319.313 4335.9389)
      (12301.145 4324.3664) (12284.0611 4311.2519) (12275.7405 4303.6183) (12272.6718 4302.6718) (12269.313 4300.8702)
      (12266.3969 4298.4885) (12264.0153 4295.5725) (12262.2137 4292.2137) (12261.2672 4289.145) (12253.6336 4280.8244)
      (12240.5191 4263.7405) (12228.9466 4245.5725) (12219.0076 4226.4733) (12210.7634 4206.5649) (12204.2901 4186.0305)
      (12199.6336 4165.0076) (12196.8244 4143.6489) (12196.3206 4132.3664) (12194.8397 4129.5267) (12193.7252 4125.8779)
    ))
    ; P3540 -- see feature_dimensions_mm.csv
    ("06_ORNAMENT" 1 (
      (12222.0611 5393.9542) (12223.2977 5386.1679) (12226.8702 5379.145) (12232.4427 5373.5725) (12239.4656 5370.0)
      (12247.2519 5368.7634) (12255.0382 5370.0) (12262.0611 5373.5725) (12267.6336 5379.145) (12271.2061 5386.1679)
      (12272.4427 5393.9542) (12271.2061 5401.7405) (12267.6336 5408.7634) (12262.0611 5414.3359) (12255.0382 5417.9084)
      (12247.2519 5419.145) (12239.4656 5417.9084) (12232.4427 5414.3359) (12226.8702 5408.7634) (12223.2977 5401.7405)
    ))
    ; P3541 -- see feature_dimensions_mm.csv
    ("06_ORNAMENT" 1 (
      (12222.0611 5232.0) (12223.2977 5224.2137) (12226.8702 5217.1908) (12232.4427 5211.6183) (12239.4656 5208.0458)
      (12247.2519 5206.8092) (12255.0382 5208.0458) (12262.0611 5211.6183) (12267.6336 5217.1908) (12271.2061 5224.2137)
      (12272.4427 5232.0) (12271.2061 5239.7863) (12267.6336 5246.8092) (12262.0611 5252.3817) (12255.0382 5255.9542)
      (12247.2519 5257.1908) (12239.4656 5255.9542) (12232.4427 5252.3817) (12226.8702 5246.8092) (12223.2977 5239.7863)
    ))
    ; P3542 -- see feature_dimensions_mm.csv
    ("06_ORNAMENT" 1 (
      (12222.0611 4798.5344) (12223.2977 4790.7481) (12226.8702 4783.7252) (12232.4427 4778.1527) (12239.4656 4774.5802)
      (12247.2519 4773.3435) (12255.0382 4774.5802) (12262.0611 4778.1527) (12267.6336 4783.7252) (12271.2061 4790.7481)
      (12272.4427 4798.5344) (12271.2061 4806.3206) (12267.6336 4813.3435) (12262.0611 4818.916) (12255.0382 4822.4885)
      (12247.2519 4823.7252) (12239.4656 4822.4885) (12232.4427 4818.916) (12226.8702 4813.3435) (12223.2977 4806.3206)
    ))
    ; P3543 -- see feature_dimensions_mm.csv
    ("06_ORNAMENT" 1 (
      (12222.0611 4636.5802) (12223.2977 4628.7939) (12226.8702 4621.771) (12232.4427 4616.1985) (12239.4656 4612.626)
      (12247.2519 4611.3893) (12255.0382 4612.626) (12262.0611 4616.1985) (12267.6336 4621.771) (12271.2061 4628.7939)
      (12272.4427 4636.5802) (12271.2061 4644.3664) (12267.6336 4651.3893) (12262.0611 4656.9618) (12255.0382 4660.5344)
      (12247.2519 4661.771) (12239.4656 4660.5344) (12232.4427 4656.9618) (12226.8702 4651.3893) (12223.2977 4644.3664)
    ))
    ; P3544 -- see feature_dimensions_mm.csv
    ("06_ORNAMENT" 1 (
      (12222.0611 4203.1145) (12223.2977 4195.3282) (12226.8702 4188.3053) (12232.4427 4182.7328) (12239.4656 4179.1603)
      (12247.2519 4177.9237) (12255.0382 4179.1603) (12262.0611 4182.7328) (12267.6336 4188.3053) (12271.2061 4195.3282)
      (12272.4427 4203.1145) (12271.2061 4210.9008) (12267.6336 4217.9237) (12262.0611 4223.4962) (12255.0382 4227.0687)
      (12247.2519 4228.3053) (12239.4656 4227.0687) (12232.4427 4223.4962) (12226.8702 4217.9237) (12223.2977 4210.9008)
    ))
    ; P3545 -- see feature_dimensions_mm.csv
    ("06_ORNAMENT" 1 (
      (12222.0611 4041.1603) (12223.2977 4033.374) (12226.8702 4026.3511) (12232.4427 4020.7786) (12239.4656 4017.2061)
      (12247.2519 4015.9695) (12255.0382 4017.2061) (12262.0611 4020.7786) (12267.6336 4026.3511) (12271.2061 4033.374)
      (12272.4427 4041.1603) (12271.2061 4048.9466) (12267.6336 4055.9695) (12262.0611 4061.542) (12255.0382 4065.1145)
      (12247.2519 4066.3511) (12239.4656 4065.1145) (12232.4427 4061.542) (12226.8702 4055.9695) (12223.2977 4048.9466)
    ))
    ; P3546 -- see feature_dimensions_mm.csv
    ("06_ORNAMENT" 1 (
      (12244.2748 1778.626) (12244.2748 1702.2901) (12256.0763 1704.1527) (12266.7023 1709.5725) (12275.1603 1718.0305)
      (12280.5802 1728.6565) (12282.4427 1740.458) (12280.5802 1752.2595) (12275.1603 1762.8855) (12266.7023 1771.3435)
      (12256.0763 1776.7634)
    ))
    ; P3547 -- see feature_dimensions_mm.csv
    ("06_ORNAMENT" 1 (
      (12244.2748 1592.2901) (12244.2748 1536.626) (12247.1145 1533.542) (12254.8244 1528.1069) (12264.0 1523.9389)
      (12274.4122 1521.1603) (12285.8168 1519.8168) (12297.9237 1519.9542) (12310.4275 1521.5725) (12323.0382 1524.6107)
      (12335.4351 1529.0076) (12347.313 1534.6565) (12358.3817 1541.4198) (12368.3664 1549.1298) (12377.0229 1557.6031)
      (12384.1374 1566.6107) (12389.5267 1575.9389) (12393.0687 1585.374) (12394.687 1594.6565) (12394.3206 1603.5878)
      (12391.9847 1611.9237) (12387.7405 1619.4656) (12381.6794 1626.0458) (12373.9695 1631.4809) (12364.7939 1635.6336)
      (12354.3817 1638.4122) (12342.9924 1639.7557) (12330.8855 1639.6183) (12318.3664 1638.0153) (12305.771 1634.9618)
      (12293.374 1630.5649) (12281.4962 1624.916) (12270.4275 1618.1527) (12260.4427 1610.4427) (12251.7863 1601.9847)
      (12244.6718 1592.9771)
    ))
    ; P3548 -- see feature_dimensions_mm.csv
    ("06_ORNAMENT" 1 (
      (12244.3817 5500.0153) (12245.8931 5494.3359) (12250.0458 5490.1985) (12255.7099 5488.6718) (12261.3893 5490.1985)
      (12265.5267 5494.3359) (12267.0534 5500.0153) (12265.5267 5505.6794) (12261.3893 5509.8321) (12255.7099 5511.3435)
      (12250.0458 5509.8321) (12245.8931 5505.6794)
    ))
    ; P3549 -- see feature_dimensions_mm.csv
    ("06_ORNAMENT" 1 (
      (12244.3817 5125.9389) (12245.8931 5120.2748) (12250.0458 5116.1221) (12255.7099 5114.6107) (12261.3893 5116.1221)
      (12265.5267 5120.2748) (12267.0534 5125.9389) (12265.5267 5131.6183) (12261.3893 5135.7557) (12255.7099 5137.2824)
      (12250.0458 5135.7557) (12245.8931 5131.6183)
    ))
    ; P3550 -- see feature_dimensions_mm.csv
    ("06_ORNAMENT" 1 (
      (12244.3817 4904.5954) (12245.8931 4898.916) (12250.0458 4894.7786) (12255.7099 4893.2519) (12261.3893 4894.7786)
      (12265.5267 4898.916) (12267.0534 4904.5954) (12265.5267 4910.2595) (12261.3893 4914.4122) (12255.7099 4915.9237)
      (12250.0458 4914.4122) (12245.8931 4910.2595)
    ))
    ; P3551 -- see feature_dimensions_mm.csv
    ("06_ORNAMENT" 1 (
      (12244.3817 4530.5191) (12245.8931 4524.855) (12250.0458 4520.7023) (12255.7099 4519.1908) (12261.3893 4520.7023)
      (12265.5267 4524.855) (12267.0534 4530.5191) (12265.5267 4536.1985) (12261.3893 4540.3359) (12255.7099 4541.8626)
      (12250.0458 4540.3359) (12245.8931 4536.1985)
    ))
    ; P3552 -- see feature_dimensions_mm.csv
    ("06_ORNAMENT" 1 (
      (12244.3817 4309.1756) (12245.8931 4303.4962) (12250.0458 4299.3588) (12255.7099 4297.8321) (12261.3893 4299.3588)
      (12265.5267 4303.4962) (12267.0534 4309.1756) (12265.5267 4314.8397) (12261.3893 4318.9924) (12255.7099 4320.5038)
      (12250.0458 4318.9924) (12245.8931 4314.8397)
    ))
    ; P3553 -- see feature_dimensions_mm.csv
    ("06_ORNAMENT" 1 (
      (12244.3817 3935.0992) (12245.8931 3929.4351) (12250.0458 3925.2824) (12255.7099 3923.771) (12261.3893 3925.2824)
      (12265.5267 3929.4351) (12267.0534 3935.0992) (12265.5267 3940.7786) (12261.3893 3944.916) (12255.7099 3946.4427)
      (12250.0458 3944.916) (12245.8931 3940.7786)
    ))
    ; P3554 -- see feature_dimensions_mm.csv
    ("06_ORNAMENT" 1 (
      (12246.626 1885.4809) (12251.7863 1878.9313) (12260.4427 1870.4733) (12270.4275 1862.7634) (12281.4962 1856.0)
      (12293.374 1850.3511) (12305.771 1845.9542) (12318.3664 1842.9008) (12330.8855 1841.2977) (12342.9924 1841.1603)
      (12354.3817 1842.5038) (12364.7939 1845.2824) (12373.9695 1849.4351) (12381.6794 1854.8702) (12387.7405 1861.4504)
      (12391.9847 1868.9924) (12394.3206 1877.3282) (12394.687 1886.2595) (12393.0687 1895.542) (12389.5267 1904.9771)
      (12384.1374 1914.3053) (12377.0229 1923.313) (12368.3664 1931.7863) (12358.3817 1939.4962) (12347.313 1946.2595)
      (12335.4351 1951.9084) (12323.0382 1956.3053) (12310.4275 1959.3435) (12297.9237 1960.9618) (12285.8168 1961.0992)
      (12274.4122 1959.7557) (12264.0 1956.9771) (12259.7099 1955.0229) (12253.0687 1928.2748) (12248.1985 1900.4733)
    ))
    ; P3555 -- see feature_dimensions_mm.csv
    ("06_ORNAMENT" 1 (
      (12253.8168 5312.9771) (12254.5344 5307.8473) (12256.6565 5302.855) (12260.1374 5298.1069) (12264.8855 5293.7252)
      (12270.7939 5289.8168) (12277.6947 5286.4885) (12285.4504 5283.8015) (12293.8473 5281.8321) (12302.687 5280.626)
      (12311.7557 5280.229) (12320.8244 5280.626) (12329.6641 5281.8321) (12338.0611 5283.8015) (12345.8168 5286.4885)
      (12352.7176 5289.8168) (12358.626 5293.7252) (12363.374 5298.1069) (12366.855 5302.855) (12368.9771 5307.8473)
      (12369.6947 5312.9771) (12368.9771 5318.1069) (12366.855 5323.0992) (12363.374 5327.8473) (12358.626 5332.229)
      (12352.7176 5336.1374) (12345.8168 5339.4656) (12338.0611 5342.1527) (12329.6641 5344.1221) (12320.8244 5345.3282)
      (12311.7557 5345.7252) (12302.687 5345.3282) (12293.8473 5344.1221) (12285.4504 5342.1527) (12277.6947 5339.4656)
      (12270.7939 5336.1374) (12264.8855 5332.229) (12260.1374 5327.8473) (12256.6565 5323.0992) (12254.5344 5318.1069)
    ))
    ; P3556 -- see feature_dimensions_mm.csv
    ("06_ORNAMENT" 1 (
      (12253.8168 4717.5573) (12254.5344 4712.4275) (12256.6565 4707.4351) (12260.1374 4702.687) (12264.8855 4698.3053)
      (12270.7939 4694.3969) (12277.6947 4691.0687) (12285.4504 4688.3817) (12293.8473 4686.4122) (12302.687 4685.2061)
      (12311.7557 4684.8092) (12320.8244 4685.2061) (12329.6641 4686.4122) (12338.0611 4688.3817) (12345.8168 4691.0687)
      (12352.7176 4694.3969) (12358.626 4698.3053) (12363.374 4702.687) (12366.855 4707.4351) (12368.9771 4712.4275)
      (12369.6947 4717.5573) (12368.9771 4722.687) (12366.855 4727.6794) (12363.374 4732.4275) (12358.626 4736.8092)
      (12352.7176 4740.7176) (12345.8168 4744.0458) (12338.0611 4746.7328) (12329.6641 4748.7023) (12320.8244 4749.9084)
      (12311.7557 4750.3053) (12302.687 4749.9084) (12293.8473 4748.7023) (12285.4504 4746.7328) (12277.6947 4744.0458)
      (12270.7939 4740.7176) (12264.8855 4736.8092) (12260.1374 4732.4275) (12256.6565 4727.6794) (12254.5344 4722.687)
    ))
    ; P3557 -- see feature_dimensions_mm.csv
    ("06_ORNAMENT" 1 (
      (12253.8168 4122.1374) (12254.5344 4117.0076) (12256.6565 4112.0153) (12260.1374 4107.2672) (12264.8855 4102.8855)
      (12270.7939 4098.9771) (12277.6947 4095.6489) (12285.4504 4092.9618) (12293.8473 4090.9924) (12302.687 4089.7863)
      (12311.7557 4089.3893) (12320.8244 4089.7863) (12329.6641 4090.9924) (12338.0611 4092.9618) (12345.8168 4095.6489)
      (12352.7176 4098.9771) (12358.626 4102.8855) (12363.374 4107.2672) (12366.855 4112.0153) (12368.9771 4117.0076)
      (12369.6947 4122.1374) (12368.9771 4127.2672) (12366.855 4132.2595) (12363.374 4137.0076) (12358.626 4141.3893)
      (12352.7176 4145.2977) (12345.8168 4148.626) (12338.0611 4151.313) (12329.6641 4153.2824) (12320.8244 4154.4885)
      (12311.7557 4154.8855) (12302.687 4154.4885) (12293.8473 4153.2824) (12285.4504 4151.313) (12277.6947 4148.626)
      (12270.7939 4145.2977) (12264.8855 4141.3893) (12260.1374 4137.0076) (12256.6565 4132.2595) (12254.5344 4127.2672)
    ))
    ; P3558 -- see feature_dimensions_mm.csv
    ("06_ORNAMENT" 1 (
      (12265.6489 5022.9008) (12266.0611 5020.3206) (12267.2519 5017.8931) (12269.145 5015.6947) (12271.6031 5013.8626)
      (12274.4427 5012.4122) (12277.4656 5011.3588) (12280.5038 5010.6412) (12283.3435 5010.1985) (12285.8626 5009.8779)
      (12287.9542 5009.5573) (12289.5878 5009.084) (12290.7481 5008.3053) (12291.5267 5007.145) (12292.0 5005.5115)
      (12292.3206 5003.4198) (12292.6412 5000.9008) (12293.084 4998.0611) (12293.8015 4995.0229) (12294.855 4992.0)
      (12296.3053 4989.1603) (12298.1374 4986.7023) (12300.3359 4984.8092) (12302.7634 4983.6183) (12305.3435 4983.2061)
      (12307.9237 4983.6183) (12310.3511 4984.8092) (12312.5496 4986.7023) (12314.3817 4989.1603) (12315.8321 4992.0)
      (12316.8855 4995.0229) (12317.6031 4998.0611) (12318.0458 5000.9008) (12318.3664 5003.4198) (12318.687 5005.5115)
      (12319.1603 5007.145) (12319.9389 5008.3053) (12321.0992 5009.084) (12322.7328 5009.5573) (12324.8244 5009.8779)
      (12327.3435 5010.1985) (12330.1832 5010.6412) (12333.2214 5011.3588) (12336.2443 5012.4122) (12339.084 5013.8626)
      (12341.542 5015.6947) (12343.4351 5017.8931) (12344.626 5020.3206) (12345.0382 5022.9008) (12344.626 5025.4809)
      (12343.4351 5027.9084) (12341.542 5030.1069) (12339.084 5031.9389) (12336.2443 5033.3893) (12333.2214 5034.4427)
      (12330.1832 5035.1603) (12327.3435 5035.6031) (12324.8244 5035.9237) (12322.7328 5036.2443) (12321.0992 5036.7176)
      (12319.9389 5037.4962) (12319.1603 5038.6565) (12318.687 5040.2901) (12318.3664 5042.3817) (12318.0458 5044.9008)
      (12317.6031 5047.7405) (12316.8855 5050.7786) (12315.8321 5053.8015) (12314.3817 5056.6412) (12312.5496 5059.0992)
      (12310.3511 5060.9924) (12307.9237 5062.1832) (12305.3435 5062.5954) (12302.7634 5062.1832) (12300.3359 5060.9924)
      (12298.1374 5059.0992) (12296.3053 5056.6412) (12294.855 5053.8015) (12293.8015 5050.7786) (12293.084 5047.7405)
      (12292.6412 5044.9008) (12292.3206 5042.3817) (12292.0 5040.2901) (12291.5267 5038.6565) (12290.7481 5037.4962)
      (12289.5878 5036.7176) (12287.9542 5036.2443) (12285.8626 5035.9237) (12283.3435 5035.6031) (12280.5038 5035.1603)
      (12277.4656 5034.4427) (12274.4427 5033.3893) (12271.6031 5031.9389) (12269.145 5030.1069) (12267.2519 5027.9084)
      (12266.0611 5025.4809)
    ))
    ; P3559 -- see feature_dimensions_mm.csv
    ("06_ORNAMENT" 1 (
      (12303.0992 5431.5878) (12303.374 5425.1298) (12304.7786 5418.1985) (12307.313 5410.9466) (12310.8855 5403.5725)
      (12315.4351 5396.2443) (12320.8397 5389.145) (12326.9618 5382.4427) (12333.6641 5376.3206) (12340.7634 5370.916)
      (12348.0916 5366.3664) (12355.4656 5362.7939) (12362.7176 5360.2595) (12369.6489 5358.8397) (12376.1069 5358.5802)
      (12381.9237 5359.4809) (12386.9618 5361.5115) (12391.084 5364.6412) (12394.2137 5368.7634) (12396.2443 5373.8015)
      (12397.145 5379.6183) (12396.8855 5386.0763) (12395.4656 5393.0076) (12392.9313 5400.2595) (12389.3588 5407.6336)
      (12384.8092 5414.9618) (12379.4046 5422.0611) (12373.2824 5428.7634) (12366.5802 5434.8855) (12359.4809 5440.2901)
      (12352.1527 5444.8397) (12344.7786 5448.4122) (12337.5267 5450.9466) (12330.5954 5452.3511) (12324.1374 5452.626)
      (12318.3206 5451.7252) (12313.2824 5449.6947) (12309.1603 5446.5649) (12306.0305 5442.4427) (12304.0 5437.4046)
    ))
    ; P3560 -- see feature_dimensions_mm.csv
    ("06_ORNAMENT" 1 (
      (12303.0992 5194.3664) (12304.0 5188.5496) (12306.0305 5183.5115) (12309.1603 5179.3893) (12313.2824 5176.2595)
      (12318.3206 5174.229) (12324.1374 5173.3282) (12330.5954 5173.6031) (12337.5267 5175.0076) (12344.7786 5177.542)
      (12352.1527 5181.1145) (12359.4809 5185.6641) (12366.5802 5191.0687) (12373.2824 5197.1908) (12379.4046 5203.8931)
      (12384.8092 5210.9924) (12389.3588 5218.3206) (12392.9313 5225.6947) (12395.4656 5232.9466) (12396.8855 5239.8779)
      (12397.145 5246.3359) (12396.2443 5252.1527) (12394.2137 5257.1908) (12391.084 5261.313) (12386.9618 5264.4427)
      (12381.9237 5266.4733) (12376.1069 5267.374) (12369.6489 5267.1145) (12362.7176 5265.6947) (12355.4656 5263.1603)
      (12348.0916 5259.5878) (12340.7634 5255.0382) (12333.6641 5249.6336) (12326.9618 5243.5115) (12320.8397 5236.8092)
      (12315.4351 5229.7099) (12310.8855 5222.3817) (12307.313 5215.0076) (12304.7786 5207.7557) (12303.374 5200.8244)
    ))
    ; P3561 -- see feature_dimensions_mm.csv
    ("06_ORNAMENT" 1 (
      (12303.0992 4836.1679) (12303.374 4829.7099) (12304.7786 4822.7786) (12307.313 4815.5267) (12310.8855 4808.1527)
      (12315.4351 4800.8244) (12320.8397 4793.7252) (12326.9618 4787.0229) (12333.6641 4780.9008) (12340.7634 4775.4962)
      (12348.0916 4770.9466) (12355.4656 4767.374) (12362.7176 4764.8397) (12369.6489 4763.4198) (12376.1069 4763.1603)
      (12381.9237 4764.0611) (12386.9618 4766.0916) (12391.084 4769.2214) (12394.2137 4773.3435) (12396.2443 4778.3817)
      (12397.145 4784.1985) (12396.8855 4790.6565) (12395.4656 4797.5878) (12392.9313 4804.8397) (12389.3588 4812.2137)
      (12384.8092 4819.542) (12379.4046 4826.6412) (12373.2824 4833.3435) (12366.5802 4839.4656) (12359.4809 4844.8702)
      (12352.1527 4849.4198) (12344.7786 4852.9924) (12337.5267 4855.5267) (12330.5954 4856.9313) (12324.1374 4857.2061)
      (12318.3206 4856.3053) (12313.2824 4854.2748) (12309.1603 4851.145) (12306.0305 4847.0229) (12304.0 4841.9847)
    ))
    ; P3562 -- see feature_dimensions_mm.csv
    ("06_ORNAMENT" 1 (
      (12303.0992 4598.9466) (12304.0 4593.1298) (12306.0305 4588.0916) (12309.1603 4583.9695) (12313.2824 4580.8397)
      (12318.3206 4578.8092) (12324.1374 4577.9084) (12330.5954 4578.1832) (12337.5267 4579.5878) (12344.7786 4582.1221)
      (12352.1527 4585.6947) (12359.4809 4590.2443) (12366.5802 4595.6489) (12373.2824 4601.771) (12379.4046 4608.4733)
      (12384.8092 4615.5725) (12389.3588 4622.9008) (12392.9313 4630.2748) (12395.4656 4637.5267) (12396.8855 4644.458)
      (12397.145 4650.916) (12396.2443 4656.7328) (12394.2137 4661.771) (12391.084 4665.8931) (12386.9618 4669.0229)
      (12381.9237 4671.0534) (12376.1069 4671.9542) (12369.6489 4671.6947) (12362.7176 4670.2748) (12355.4656 4667.7405)
      (12348.0916 4664.1679) (12340.7634 4659.6183) (12333.6641 4654.2137) (12326.9618 4648.0916) (12320.8397 4641.3893)
      (12315.4351 4634.2901) (12310.8855 4626.9618) (12307.313 4619.5878) (12304.7786 4612.3359) (12303.374 4605.4046)
    ))
    ; P3563 -- see feature_dimensions_mm.csv
    ("06_ORNAMENT" 1 (
      (12303.0992 4240.7481) (12303.374 4234.2901) (12304.7786 4227.3588) (12307.313 4220.1069) (12310.8855 4212.7328)
      (12315.4351 4205.4046) (12320.8397 4198.3053) (12326.9618 4191.6031) (12333.6641 4185.4809) (12340.7634 4180.0763)
      (12348.0916 4175.5267) (12355.4656 4171.9542) (12362.7176 4169.4198) (12369.6489 4168.0) (12376.1069 4167.7405)
      (12381.9237 4168.6412) (12386.9618 4170.6718) (12391.084 4173.8015) (12394.2137 4177.9237) (12396.2443 4182.9618)
      (12397.145 4188.7786) (12396.8855 4195.2366) (12395.4656 4202.1679) (12392.9313 4209.4198) (12389.3588 4216.7939)
      (12384.8092 4224.1221) (12379.4046 4231.2214) (12373.2824 4237.9237) (12366.5802 4244.0458) (12359.4809 4249.4504)
      (12352.1527 4254.0) (12344.7786 4257.5725) (12337.5267 4260.1069) (12330.5954 4261.5115) (12324.1374 4261.7863)
      (12318.3206 4260.8855) (12313.2824 4258.855) (12309.1603 4255.7252) (12306.0305 4251.6031) (12304.0 4246.5649)
    ))
    ; P3564 -- see feature_dimensions_mm.csv
    ("06_ORNAMENT" 1 (
      (12303.0992 4003.5267) (12304.0 3997.7099) (12306.0305 3992.6718) (12309.1603 3988.5496) (12313.2824 3985.4198)
      (12318.3206 3983.3893) (12324.1374 3982.4885) (12330.5954 3982.7634) (12337.5267 3984.1679) (12344.7786 3986.7023)
      (12352.1527 3990.2748) (12359.4809 3994.8244) (12366.5802 4000.229) (12373.2824 4006.3511) (12379.4046 4013.0534)
      (12384.8092 4020.1527) (12389.3588 4027.4809) (12392.9313 4034.855) (12395.4656 4042.1069) (12396.8855 4049.0382)
      (12397.145 4055.4962) (12396.2443 4061.313) (12394.2137 4066.3511) (12391.084 4070.4733) (12386.9618 4073.6031)
      (12381.9237 4075.6336) (12376.1069 4076.5344) (12369.6489 4076.2748) (12362.7176 4074.855) (12355.4656 4072.3206)
      (12348.0916 4068.7481) (12340.7634 4064.1985) (12333.6641 4058.7939) (12326.9618 4052.6718) (12320.8397 4045.9695)
      (12315.4351 4038.8702) (12310.8855 4031.542) (12307.313 4024.1679) (12304.7786 4016.916) (12303.374 4009.9847)
    ))
    ; P3565 -- see feature_dimensions_mm.csv
    ("06_ORNAMENT" 1 (
      (12305.3435 1740.458) (12307.0382 1728.5191) (12312.0611 1716.8702) (12320.3206 1705.8015) (12331.5878 1695.5878)
      (12345.5878 1686.4733) (12361.9847 1678.7023) (12380.3664 1672.4427) (12400.2901 1667.8626) (12421.2519 1665.0687)
      (12442.7481 1664.1221) (12464.2443 1665.0687) (12485.2061 1667.8626) (12505.1298 1672.4427) (12523.5115 1678.7023)
      (12539.9084 1686.4733) (12553.9084 1695.5878) (12565.1756 1705.8015) (12573.4351 1716.8702) (12578.458 1728.5191)
      (12580.1527 1740.458) (12578.458 1752.3969) (12573.4351 1764.0458) (12565.1756 1775.1145) (12553.9084 1785.3282)
      (12539.9084 1794.4427) (12523.5115 1802.2137) (12505.1298 1808.4733) (12485.2061 1813.0534) (12464.2443 1815.8473)
      (12442.7481 1816.7939) (12421.2519 1815.8473) (12400.2901 1813.0534) (12380.3664 1808.4733) (12361.9847 1802.2137)
      (12345.5878 1794.4427) (12331.5878 1785.3282) (12320.3206 1775.1145) (12312.0611 1764.0458) (12307.0382 1752.3969)
    ))
    ; P3566 -- see feature_dimensions_mm.csv
    ("06_ORNAMENT" 1 (
      (12330.1985 5068.6107) (12331.7099 5062.9466) (12335.8626 5058.7939) (12341.5267 5057.2672) (12347.1908 5058.7939)
      (12351.3435 5062.9466) (12352.8702 5068.6107) (12351.3435 5074.2748) (12347.1908 5078.4275) (12341.5267 5079.9389)
      (12335.8626 5078.4275) (12331.7099 5074.2748)
    ))
    ; P3567 -- see feature_dimensions_mm.csv
    ("06_ORNAMENT" 1 (
      (12330.1985 4961.9237) (12331.7099 4956.2595) (12335.8626 4952.1069) (12341.5267 4950.5954) (12347.1908 4952.1069)
      (12351.3435 4956.2595) (12352.8702 4961.9237) (12351.3435 4967.5878) (12347.1908 4971.7405) (12341.5267 4973.2672)
      (12335.8626 4971.7405) (12331.7099 4967.5878)
    ))
    ; P3568 -- see feature_dimensions_mm.csv
    ("06_ORNAMENT" 1 (
      (12330.1985 4366.5038) (12331.7099 4360.8397) (12335.8626 4356.687) (12341.5267 4355.1756) (12347.1908 4356.687)
      (12351.3435 4360.8397) (12352.8702 4366.5038) (12351.3435 4372.1679) (12347.1908 4376.3206) (12341.5267 4377.8473)
      (12335.8626 4376.3206) (12331.7099 4372.1679)
    ))
    ; P3569 -- see feature_dimensions_mm.csv
    ("06_ORNAMENT" 1 (
      (12330.1985 3877.771) (12331.7099 3872.1069) (12335.8626 3867.9542) (12341.5267 3866.4275) (12347.1908 3867.9542)
      (12351.3435 3872.1069) (12352.8702 3877.771) (12351.3435 3883.4351) (12347.1908 3887.5878) (12341.5267 3889.0992)
      (12335.8626 3887.5878) (12331.7099 3883.4351)
    ))
    ; P3570 -- see feature_dimensions_mm.csv
    ("06_ORNAMENT" 1 (
      (12336.5802 5117.4809) (12337.8168 5109.6947) (12341.3893 5102.6718) (12346.9618 5097.0992) (12353.9847 5093.5267)
      (12361.771 5092.2901) (12369.5573 5093.5267) (12376.5802 5097.0992) (12382.1527 5102.6718) (12385.7252 5109.6947)
      (12386.9618 5117.4809) (12385.7252 5125.2672) (12382.1527 5132.2901) (12376.5802 5137.8626) (12369.5573 5141.4351)
      (12361.771 5142.6718) (12353.9847 5141.4351) (12346.9618 5137.8626) (12341.3893 5132.2901) (12337.8168 5125.2672)
    ))
    ; P3571 -- see feature_dimensions_mm.csv
    ("06_ORNAMENT" 1 (
      (12336.5802 4913.0534) (12337.8168 4905.2672) (12341.3893 4898.2443) (12346.9618 4892.6718) (12353.9847 4889.0992)
      (12361.771 4887.8626) (12369.5573 4889.0992) (12376.5802 4892.6718) (12382.1527 4898.2443) (12385.7252 4905.2672)
      (12386.9618 4913.0534) (12385.7252 4920.8397) (12382.1527 4927.8626) (12376.5802 4933.4351) (12369.5573 4937.0076)
      (12361.771 4938.2443) (12353.9847 4937.0076) (12346.9618 4933.4351) (12341.3893 4927.8626) (12337.8168 4920.8397)
    ))
    ; P3572 -- see feature_dimensions_mm.csv
    ("06_ORNAMENT" 1 (
      (12336.5802 4522.0611) (12337.8168 4514.2748) (12341.3893 4507.2519) (12346.9618 4501.6794) (12353.9847 4498.1069)
      (12361.771 4496.8702) (12369.5573 4498.1069) (12376.5802 4501.6794) (12382.1527 4507.2519) (12385.7252 4514.2748)
      (12386.9618 4522.0611) (12385.7252 4529.8473) (12382.1527 4536.8702) (12376.5802 4542.4427) (12369.5573 4546.0153)
      (12361.771 4547.2519) (12353.9847 4546.0153) (12346.9618 4542.4427) (12341.3893 4536.8702) (12337.8168 4529.8473)
    ))
    ; P3573 -- see feature_dimensions_mm.csv
    ("06_ORNAMENT" 1 (
      (12336.5802 4317.6336) (12337.8168 4309.8473) (12341.3893 4302.8244) (12346.9618 4297.2519) (12353.9847 4293.6794)
      (12361.771 4292.4427) (12369.5573 4293.6794) (12376.5802 4297.2519) (12382.1527 4302.8244) (12385.7252 4309.8473)
      (12386.9618 4317.6336) (12385.7252 4325.4198) (12382.1527 4332.4427) (12376.5802 4338.0153) (12369.5573 4341.5878)
      (12361.771 4342.8244) (12353.9847 4341.5878) (12346.9618 4338.0153) (12341.3893 4332.4427) (12337.8168 4325.4198)
    ))
    ; P3574 -- see feature_dimensions_mm.csv
    ("06_ORNAMENT" 1 (
      (12336.5802 3926.6412) (12337.8168 3918.855) (12341.3893 3911.8321) (12346.9618 3906.2595) (12353.9847 3902.687)
      (12361.771 3901.4504) (12369.5573 3902.687) (12376.5802 3906.2595) (12382.1527 3911.8321) (12385.7252 3918.855)
      (12386.9618 3926.6412) (12385.7252 3934.4275) (12382.1527 3941.4504) (12376.5802 3947.0229) (12369.5573 3950.5954)
      (12361.771 3951.8321) (12353.9847 3950.5954) (12346.9618 3947.0229) (12341.3893 3941.4504) (12337.8168 3934.4275)
    ))
    ; P3575 -- see feature_dimensions_mm.csv
    ("06_ORNAMENT" 1 (
      (12340.2595 2064.3206) (12342.1221 2052.5344) (12347.542 2041.8931) (12355.9847 2033.4504) (12366.626 2028.0305)
      (12378.4275 2026.1527) (12390.2137 2028.0305) (12400.855 2033.4504) (12409.2977 2041.8931) (12414.7176 2052.5344)
      (12416.5954 2064.3206) (12414.7176 2076.1221) (12409.2977 2086.7634) (12400.855 2095.2061) (12390.2137 2100.626)
      (12378.4275 2102.4885) (12366.626 2100.626) (12355.9847 2095.2061) (12347.542 2086.7634) (12342.1221 2076.1221)
    ))
    ; P3576 -- see feature_dimensions_mm.csv
    ("06_ORNAMENT" 1 (
      (12340.2595 1416.5954) (12342.1221 1404.7939) (12347.542 1394.1527) (12355.9847 1385.7099) (12366.626 1380.2901)
      (12378.4275 1378.4275) (12384.3359 1379.3588) (12382.916 1377.9695) (12381.6794 1374.0458) (12382.916 1370.1221)
      (12386.458 1366.6412) (12391.7252 1363.8931) (12397.9237 1362.0305) (12404.1069 1360.9313) (12409.4504 1360.2443)
      (12413.2672 1359.5115) (12415.2519 1358.1679) (12415.4198 1355.7863) (12414.1527 1352.1069) (12412.0763 1347.145)
      (12409.9237 1341.2214) (12408.4427 1334.9313) (12408.1832 1329.0076) (12409.4351 1324.1985) (12412.2137 1321.1603)
      (12416.229 1320.2748) (12421.0229 1321.5878) (12426.0305 1324.7786) (12430.7328 1329.2214) (12434.7939 1334.0305)
      (12438.0458 1338.3053) (12440.5954 1341.2519) (12442.7481 1342.2901) (12444.9008 1341.2519) (12447.4504 1338.3053)
      (12450.7023 1334.0305) (12454.7634 1329.2214) (12459.4656 1324.7786) (12464.4733 1321.5878) (12469.2672 1320.2748)
      (12473.2824 1321.1603) (12476.0611 1324.1985) (12477.313 1329.0076) (12477.0534 1334.9313) (12475.5725 1341.2214)
      (12473.4198 1347.145) (12471.3435 1352.1069) (12470.0763 1355.7863) (12470.2443 1358.1679) (12472.229 1359.5115)
      (12476.0458 1360.2443) (12481.3893 1360.9313) (12486.6718 1361.8779) (12486.4427 1361.2061) (12483.4046 1348.5954)
      (12481.7863 1336.0916) (12481.6489 1323.9847) (12482.9924 1312.5802) (12485.771 1302.1679) (12489.9389 1292.9924)
      (12495.374 1285.2824) (12501.9389 1279.2366) (12509.4809 1274.9924) (12517.8321 1272.6565) (12526.7481 1272.2901)
      (12536.0458 1273.8931) (12545.4656 1277.4504) (12554.8092 1282.8397) (12563.8168 1289.9542) (12572.2748 1298.6107)
      (12579.9847 1308.5954) (12586.7481 1319.6641) (12592.3969 1331.542) (12596.7939 1343.9389) (12599.8473 1356.5344)
      (12601.4504 1369.0534) (12601.5878 1381.145) (12600.2443 1392.5496) (12597.4656 1402.9618) (12593.313 1412.1374)
      (12587.8779 1419.8473) (12581.2977 1425.9084) (12573.7557 1430.1527) (12565.4198 1432.4885) (12556.4885 1432.855)
      (12547.2061 1431.2366) (12537.771 1427.6947) (12528.4427 1422.3053) (12519.4351 1415.1908) (12510.9618 1406.5344)
      (12503.2519 1396.5496) (12496.4885 1385.4809) (12495.4656 1383.313) (12493.771 1384.1985) (12487.5725 1386.0611)
      (12481.3893 1387.1603) (12476.0458 1387.8473) (12472.229 1388.5802) (12470.2443 1389.9237) (12470.0763 1392.3053)
      (12471.3435 1395.9847) (12473.4198 1400.9466) (12475.5725 1406.8702) (12477.0534 1413.1603) (12477.313 1419.084)
      (12476.0611 1423.8931) (12473.2824 1426.9313) (12469.2672 1427.8168) (12464.4733 1426.5038) (12459.4656 1423.313)
      (12454.7634 1418.8702) (12450.7023 1414.0611) (12447.4504 1409.7863) (12444.9008 1406.8397) (12442.7481 1405.8015)
      (12440.5954 1406.8397) (12438.0458 1409.7863) (12434.7939 1414.0611) (12430.7328 1418.8702) (12426.0305 1423.313)
      (12421.0229 1426.5038) (12416.229 1427.8168) (12414.855 1427.5115) (12414.7176 1428.3817) (12409.2977 1439.0229)
      (12400.855 1447.4656) (12390.2137 1452.8855) (12378.4275 1454.7634) (12366.626 1452.8855) (12355.9847 1447.4656)
      (12347.542 1439.0229) (12342.1221 1428.3817)
    ))
    ; P3577 -- see feature_dimensions_mm.csv
    ("06_ORNAMENT" 1 (
      (12381.6794 2137.4046) (12382.916 2133.4809) (12386.458 2130.0) (12391.7252 2127.2519) (12397.9237 2125.3893)
      (12404.1069 2124.2901) (12409.4504 2123.6031) (12413.2672 2122.8702) (12415.2519 2121.5267) (12415.4198 2119.145)
      (12414.1527 2115.4656) (12412.0763 2110.5038) (12409.9237 2104.5802) (12408.4427 2098.2901) (12408.1832 2092.3664)
      (12409.4351 2087.5573) (12412.2137 2084.5191) (12416.229 2083.6336) (12421.0229 2084.9466) (12426.0305 2088.1374)
      (12430.7328 2092.5802) (12434.7939 2097.3893) (12438.0458 2101.6641) (12440.5954 2104.6107) (12442.7481 2105.6489)
      (12444.9008 2104.6107) (12447.4504 2101.6641) (12450.7023 2097.3893) (12454.7634 2092.5802) (12459.4656 2088.1374)
      (12464.4733 2084.9466) (12469.2672 2083.6336) (12473.2824 2084.5191) (12476.0611 2087.5573) (12477.313 2092.3664)
      (12477.0534 2098.2901) (12475.5725 2104.5802) (12473.4198 2110.5038) (12471.3435 2115.4656) (12470.0763 2119.145)
      (12470.2443 2121.5267) (12472.229 2122.8702) (12476.0458 2123.6031) (12481.3893 2124.2901) (12485.1756 2124.9618)
      (12486.4427 2119.7099) (12490.8397 2107.313) (12496.4885 2095.4351) (12503.2519 2084.3664) (12510.9618 2074.3817)
      (12519.4351 2065.7252) (12528.4427 2058.6107) (12537.771 2053.2214) (12547.2061 2049.6794) (12556.4885 2048.0611)
      (12565.4198 2048.4275) (12573.7557 2050.7634) (12581.2977 2055.0076) (12587.8779 2061.0687) (12593.313 2068.7786)
      (12597.4656 2077.9542) (12600.2443 2088.3664) (12601.5878 2099.7557) (12601.4504 2111.8626) (12599.8473 2124.3817)
      (12596.7939 2136.9771) (12592.3969 2149.374) (12586.7481 2161.2519) (12579.9847 2172.3206) (12572.2748 2182.3053)
      (12563.8168 2190.9618) (12554.8092 2198.0763) (12545.4656 2203.4656) (12536.0458 2207.0229) (12526.7481 2208.626)
      (12517.8321 2208.2595) (12509.4809 2205.9237) (12501.9389 2201.6794) (12495.374 2195.6336) (12489.9389 2187.9237)
      (12485.771 2178.7481) (12482.9924 2168.3359) (12481.6489 2156.9313) (12481.7252 2150.458) (12481.3893 2150.5191)
      (12476.0458 2151.2061) (12472.229 2151.9389) (12470.2443 2153.2824) (12470.0763 2155.6641) (12471.3435 2159.3435)
      (12473.4198 2164.3053) (12475.5725 2170.229) (12477.0534 2176.5191) (12477.313 2182.4427) (12476.0611 2187.2519)
      (12473.2824 2190.2901) (12469.2672 2191.1756) (12464.4733 2189.8626) (12459.4656 2186.6718) (12454.7634 2182.229)
      (12450.7023 2177.4198) (12447.4504 2173.145) (12444.9008 2170.1985) (12442.7481 2169.1603) (12440.5954 2170.1985)
      (12438.0458 2173.145) (12434.7939 2177.4198) (12430.7328 2182.229) (12426.0305 2186.6718) (12425.3435 2187.0992)
      (12423.4656 2185.8473) (12408.9008 2174.5954) (12409.9237 2170.229) (12412.0763 2164.3053) (12414.1527 2159.3435)
      (12415.4198 2155.6641) (12415.2519 2153.2824) (12413.2672 2151.9389) (12409.4504 2151.2061) (12404.1069 2150.5191)
      (12397.9237 2149.4198) (12391.7252 2147.5573) (12386.458 2144.8092) (12382.916 2141.3282)
    ))
    ; P3578 -- see feature_dimensions_mm.csv
    ("06_ORNAMENT" 1 (
      (12382.2901 5312.9771) (12383.4504 5301.1756) (12386.8855 5289.8473) (12392.4733 5279.3893) (12400.0 5270.229)
      (12409.1603 5262.7023) (12419.6183 5257.1145) (12430.9466 5253.6794) (12442.7481 5252.5191) (12454.5496 5253.6794)
      (12465.8779 5257.1145) (12476.3359 5262.7023) (12485.4962 5270.229) (12493.0229 5279.3893) (12498.6107 5289.8473)
      (12502.0458 5301.1756) (12503.2061 5312.9771) (12502.0458 5324.7786) (12498.6107 5336.1069) (12493.0229 5346.5649)
      (12485.4962 5355.7252) (12476.3359 5363.2519) (12465.8779 5368.8397) (12454.5496 5372.2748) (12442.7481 5373.4351)
      (12430.9466 5372.2748) (12419.6183 5368.8397) (12409.1603 5363.2519) (12400.0 5355.7252) (12392.4733 5346.5649)
      (12386.8855 5336.1069) (12383.4504 5324.7786)
    ))
    ; P3579 -- see feature_dimensions_mm.csv
    ("06_ORNAMENT" 1 (
      (12382.2901 4717.5573) (12383.4504 4705.7557) (12386.8855 4694.4275) (12392.4733 4683.9695) (12400.0 4674.8092)
      (12409.1603 4667.2824) (12419.6183 4661.6947) (12430.9466 4658.2595) (12442.7481 4657.0992) (12454.5496 4658.2595)
      (12465.8779 4661.6947) (12476.3359 4667.2824) (12485.4962 4674.8092) (12493.0229 4683.9695) (12498.6107 4694.4275)
      (12502.0458 4705.7557) (12503.2061 4717.5573) (12502.0458 4729.3588) (12498.6107 4740.687) (12493.0229 4751.145)
      (12485.4962 4760.3053) (12476.3359 4767.8321) (12465.8779 4773.4198) (12454.5496 4776.855) (12442.7481 4778.0153)
      (12430.9466 4776.855) (12419.6183 4773.4198) (12409.1603 4767.8321) (12400.0 4760.3053) (12392.4733 4751.145)
      (12386.8855 4740.687) (12383.4504 4729.3588)
    ))
    ; P3580 -- see feature_dimensions_mm.csv
    ("06_ORNAMENT" 1 (
      (12382.2901 4122.1374) (12383.4504 4110.3359) (12386.8855 4099.0076) (12392.4733 4088.5496) (12400.0 4079.3893)
      (12409.1603 4071.8626) (12419.6183 4066.2748) (12430.9466 4062.8397) (12442.7481 4061.6794) (12454.5496 4062.8397)
      (12465.8779 4066.2748) (12476.3359 4071.8626) (12485.4962 4079.3893) (12493.0229 4088.5496) (12498.6107 4099.0076)
      (12502.0458 4110.3359) (12503.2061 4122.1374) (12502.0458 4133.9389) (12498.6107 4145.2672) (12493.0229 4155.7252)
      (12485.4962 4164.8855) (12476.3359 4172.4122) (12465.8779 4178.0) (12454.5496 4181.4351) (12442.7481 4182.5954)
      (12430.9466 4181.4351) (12419.6183 4178.0) (12409.1603 4172.4122) (12400.0 4164.8855) (12392.4733 4155.7252)
      (12386.8855 4145.2672) (12383.4504 4133.9389)
    ))
    ; P3581 -- see feature_dimensions_mm.csv
    ("06_ORNAMENT" 1 (
      (12401.9084 1386.7634) (12409.2977 1394.1527) (12412.3817 1400.1985) (12414.1527 1395.9847) (12415.4198 1392.3053)
      (12415.2519 1389.9237) (12413.2672 1388.5802) (12409.4504 1387.8473) (12404.1069 1387.1603)
    ))
    ; P3582 -- see feature_dimensions_mm.csv
    ("06_ORNAMENT" 1 (
      (12407.4809 5312.9771) (12408.687 5303.8473) (12412.1985 5295.3435) (12417.8168 5288.0458) (12425.1145 5282.4275)
      (12433.6183 5278.916) (12442.7481 5277.7099) (12451.8779 5278.916) (12460.3817 5282.4275) (12467.6794 5288.0458)
      (12473.2977 5295.3435) (12476.8092 5303.8473) (12478.0153 5312.9771) (12476.8092 5322.1069) (12473.2977 5330.6107)
      (12467.6794 5337.9084) (12460.3817 5343.5267) (12451.8779 5347.0382) (12442.7481 5348.2443) (12433.6183 5347.0382)
      (12425.1145 5343.5267) (12417.8168 5337.9084) (12412.1985 5330.6107) (12408.687 5322.1069)
    ))
    ; P3583 -- see feature_dimensions_mm.csv
    ("06_ORNAMENT" 1 (
      (12407.4809 4717.5573) (12408.687 4708.4275) (12412.1985 4699.9237) (12417.8168 4692.626) (12425.1145 4687.0076)
      (12433.6183 4683.4962) (12442.7481 4682.2901) (12451.8779 4683.4962) (12460.3817 4687.0076) (12467.6794 4692.626)
      (12473.2977 4699.9237) (12476.8092 4708.4275) (12478.0153 4717.5573) (12476.8092 4726.687) (12473.2977 4735.1908)
      (12467.6794 4742.4885) (12460.3817 4748.1069) (12451.8779 4751.6183) (12442.7481 4752.8244) (12433.6183 4751.6183)
      (12425.1145 4748.1069) (12417.8168 4742.4885) (12412.1985 4735.1908) (12408.687 4726.687)
    ))
    ; P3584 -- see feature_dimensions_mm.csv
    ("06_ORNAMENT" 1 (
      (12407.4809 4122.1374) (12408.687 4113.0076) (12412.1985 4104.5038) (12417.8168 4097.2061) (12425.1145 4091.5878)
      (12433.6183 4088.0763) (12442.7481 4086.8702) (12451.8779 4088.0763) (12460.3817 4091.5878) (12467.6794 4097.2061)
      (12473.2977 4104.5038) (12476.8092 4113.0076) (12478.0153 4122.1374) (12476.8092 4131.2672) (12473.2977 4139.771)
      (12467.6794 4147.0687) (12460.3817 4152.687) (12451.8779 4156.1985) (12442.7481 4157.4046) (12433.6183 4156.1985)
      (12425.1145 4152.687) (12417.8168 4147.0687) (12412.1985 4139.771) (12408.687 4131.2672)
    ))
    ; P3585 -- see feature_dimensions_mm.csv
    ("06_ORNAMENT" 1 (
      (12407.6947 1986.0458) (12408.4427 1970.855) (12411.8931 1954.5191) (12417.9847 1937.4198) (12426.5649 1920.0)
      (12437.4046 1902.6718) (12450.2595 1885.8626) (12464.7939 1870.0) (12480.6565 1855.4656) (12497.4504 1842.626)
      (12514.7786 1831.771) (12532.2137 1823.2061) (12549.2977 1817.1145) (12565.6489 1813.6489) (12580.8244 1812.9008)
      (12594.4885 1814.9008) (12606.2901 1819.5725) (12615.9237 1826.8244) (12623.1756 1836.458) (12627.8473 1848.2595)
      (12629.8473 1861.9237) (12629.0992 1877.0992) (12625.6336 1893.4504) (12619.542 1910.5344) (12610.9771 1927.9695)
      (12600.1221 1945.2977) (12587.2824 1962.0916) (12572.7481 1977.9542) (12556.8855 1992.4885) (12540.0763 2005.3435)
      (12522.7481 2016.1832) (12505.3282 2024.7634) (12488.229 2030.855) (12471.8931 2034.3053) (12456.7023 2035.0534)
      (12443.0382 2033.0687) (12431.2519 2028.3817) (12421.6031 2021.145) (12414.3664 2011.4962) (12409.6794 1999.7099)
    ))
    ; P3586 -- see feature_dimensions_mm.csv
    ("06_ORNAMENT" 1 (
      (12407.6947 1494.8702) (12409.6794 1481.2061) (12414.3664 1469.4198) (12421.6031 1459.771) (12431.2519 1452.5191)
      (12443.0382 1447.8473) (12456.7023 1445.8626) (12471.8931 1446.5954) (12488.229 1450.0611) (12505.3282 1456.1527)
      (12522.7481 1464.7328) (12540.0763 1475.5725) (12556.8855 1488.4275) (12572.7481 1502.9618) (12587.2824 1518.8244)
      (12600.1221 1535.6183) (12610.9771 1552.9466) (12619.542 1570.3817) (12625.6336 1587.4656) (12629.0992 1603.8168)
      (12629.8473 1618.9924) (12627.8473 1632.6565) (12623.1756 1644.458) (12615.9237 1654.0916) (12606.2901 1661.3435)
      (12594.4885 1666.0153) (12580.8244 1668.0153) (12565.6489 1667.2672) (12549.2977 1663.8015) (12532.2137 1657.7099)
      (12514.7786 1649.145) (12497.4504 1638.2901) (12480.6565 1625.4504) (12464.7939 1610.916) (12450.2595 1595.0534)
      (12437.4046 1578.2443) (12426.5649 1560.916) (12417.9847 1543.4962) (12411.8931 1526.3969) (12408.4427 1510.0611)
    ))
    ; P3587 -- see feature_dimensions_mm.csv
    ("06_ORNAMENT" 1 (
      (12410.0 5181.9847) (12410.3969 5172.916) (12411.6031 5164.0763) (12413.5725 5155.6794) (12416.2595 5147.9237)
      (12419.5878 5141.0229) (12423.4962 5135.1145) (12427.8779 5130.3664) (12432.626 5126.8855) (12437.6183 5124.7634)
      (12442.7481 5124.0458) (12447.8779 5124.7634) (12452.8702 5126.8855) (12457.6183 5130.3664) (12462.0 5135.1145)
      (12465.9084 5141.0229) (12469.2366 5147.9237) (12471.9237 5155.6794) (12473.8931 5164.0763) (12475.0992 5172.916)
      (12475.4962 5181.9847) (12475.0992 5191.0534) (12473.8931 5199.8931) (12471.9237 5208.2901) (12469.2366 5216.0458)
      (12465.9084 5222.9466) (12462.0 5228.855) (12457.6183 5233.6031) (12452.8702 5237.084) (12447.8779 5239.2061)
      (12442.7481 5239.9237) (12437.6183 5239.2061) (12432.626 5237.084) (12427.8779 5233.6031) (12423.4962 5228.855)
      (12419.5878 5222.9466) (12416.2595 5216.0458) (12413.5725 5208.2901) (12411.6031 5199.8931) (12410.3969 5191.0534)
    ))
    ; P3588 -- see feature_dimensions_mm.csv
    ("06_ORNAMENT" 1 (
      (12410.0 4848.5496) (12410.3969 4839.4809) (12411.6031 4830.6412) (12413.5725 4822.2443) (12416.2595 4814.4885)
      (12419.5878 4807.5878) (12423.4962 4801.6794) (12427.8779 4796.9313) (12432.626 4793.4504) (12437.6183 4791.3282)
      (12442.7481 4790.6107) (12447.8779 4791.3282) (12452.8702 4793.4504) (12457.6183 4796.9313) (12462.0 4801.6794)
      (12465.9084 4807.5878) (12469.2366 4814.4885) (12471.9237 4822.2443) (12473.8931 4830.6412) (12475.0992 4839.4809)
      (12475.4962 4848.5496) (12475.0992 4857.6183) (12473.8931 4866.458) (12471.9237 4874.855) (12469.2366 4882.6107)
      (12465.9084 4889.5115) (12462.0 4895.4198) (12457.6183 4900.1679) (12452.8702 4903.6489) (12447.8779 4905.771)
      (12442.7481 4906.4885) (12437.6183 4905.771) (12432.626 4903.6489) (12427.8779 4900.1679) (12423.4962 4895.4198)
      (12419.5878 4889.5115) (12416.2595 4882.6107) (12413.5725 4874.855) (12411.6031 4866.458) (12410.3969 4857.6183)
    ))
    ; P3589 -- see feature_dimensions_mm.csv
    ("06_ORNAMENT" 1 (
      (12410.0 4253.1298) (12410.3969 4244.0611) (12411.6031 4235.2214) (12413.5725 4226.8244) (12416.2595 4219.0687)
      (12419.5878 4212.1679) (12423.4962 4206.2595) (12427.8779 4201.5115) (12432.626 4198.0305) (12437.6183 4195.9084)
      (12442.7481 4195.1908) (12447.8779 4195.9084) (12452.8702 4198.0305) (12457.6183 4201.5115) (12462.0 4206.2595)
      (12465.9084 4212.1679) (12469.2366 4219.0687) (12471.9237 4226.8244) (12473.8931 4235.2214) (12475.0992 4244.0611)
      (12475.4962 4253.1298) (12475.0992 4262.1985) (12473.8931 4271.0382) (12471.9237 4279.4351) (12469.2366 4287.1908)
      (12465.9084 4294.0916) (12462.0 4300.0) (12457.6183 4304.7481) (12452.8702 4308.229) (12447.8779 4310.3511)
      (12442.7481 4311.0687) (12437.6183 4310.3511) (12432.626 4308.229) (12427.8779 4304.7481) (12423.4962 4300.0)
      (12419.5878 4294.0916) (12416.2595 4287.1908) (12413.5725 4279.4351) (12411.6031 4271.0382) (12410.3969 4262.1985)
    ))
    ; P3590 -- see feature_dimensions_mm.csv
    ("06_ORNAMENT" 1 (
      (12410.0 3991.145) (12410.3969 3982.0763) (12411.6031 3973.2366) (12413.5725 3964.8397) (12416.2595 3957.084)
      (12419.5878 3950.1832) (12423.4962 3944.2748) (12427.8779 3939.5267) (12432.626 3936.0458) (12437.6183 3933.9237)
      (12442.7481 3933.2061) (12447.8779 3933.9237) (12452.8702 3936.0458) (12457.6183 3939.5267) (12462.0 3944.2748)
      (12465.9084 3950.1832) (12469.2366 3957.084) (12471.9237 3964.8397) (12473.8931 3973.2366) (12475.0992 3982.0763)
      (12475.4962 3991.145) (12475.0992 4000.2137) (12473.8931 4009.0534) (12471.9237 4017.4504) (12469.2366 4025.2061)
      (12465.9084 4032.1069) (12462.0 4038.0153) (12457.6183 4042.7634) (12452.8702 4046.2443) (12447.8779 4048.3664)
      (12442.7481 4049.084) (12437.6183 4048.3664) (12432.626 4046.2443) (12427.8779 4042.7634) (12423.4962 4038.0153)
      (12419.5878 4032.1069) (12416.2595 4025.2061) (12413.5725 4017.4504) (12411.6031 4009.0534) (12410.3969 4000.2137)
    ))
    ; P3591 -- see feature_dimensions_mm.csv
    ("06_ORNAMENT" 1 (
      (12431.4198 5048.4733) (12432.9313 5042.8092) (12437.084 5038.6565) (12442.7481 5037.1298) (12448.4122 5038.6565)
      (12452.5649 5042.8092) (12454.0916 5048.4733) (12452.5649 5054.1374) (12448.4122 5058.2901) (12442.7481 5059.8015)
      (12437.084 5058.2901) (12432.9313 5054.1374)
    ))
    ; P3592 -- see feature_dimensions_mm.csv
    ("06_ORNAMENT" 1 (
      (12431.4198 3857.6336) (12432.9313 3851.9695) (12437.084 3847.8168) (12442.7481 3846.2901) (12448.4122 3847.8168)
      (12452.5649 3851.9695) (12454.0916 3857.6336) (12452.5649 3863.2977) (12448.4122 3867.4504) (12442.7481 3868.9618)
      (12437.084 3867.4504) (12432.9313 3863.2977)
    ))
    ; P3593 -- see feature_dimensions_mm.csv
    ("06_ORNAMENT" 1 (
      (12452.5191 3007.6336) (12453.2366 3006.3206) (12455.1603 3005.2519) (12457.8015 3004.5496) (12460.4427 3004.1985)
      (12462.4275 3003.9542) (12463.313 3003.4962) (12463.0076 3002.5649) (12461.771 3000.9924) (12460.1679 2998.8702)
      (12458.7939 2996.5038) (12458.1679 2994.3817) (12458.5954 2992.9466) (12460.0305 2992.5191) (12462.1527 2993.145)
      (12464.5191 2994.5191) (12466.6412 2996.1221) (12468.2137 2997.3588) (12469.145 2997.6641) (12469.6031 2996.7786)
      (12469.8473 2994.7939) (12470.1985 2992.1527) (12470.9008 2989.5115) (12471.9695 2987.5878) (12473.2824 2986.8702)
      (12474.5954 2987.5878) (12475.6641 2989.5115) (12476.3664 2992.1527) (12476.7176 2994.7939) (12476.9618 2996.7786)
      (12477.4198 2997.6641) (12478.3511 2997.3588) (12479.9237 2996.1221) (12482.0458 2994.5191) (12484.4122 2993.145)
      (12486.5344 2992.5191) (12487.9695 2992.9466) (12488.3969 2994.3817) (12487.771 2996.5038) (12486.3969 2998.8702)
      (12484.7939 3000.9924) (12483.5573 3002.5649) (12483.2519 3003.4962) (12484.1374 3003.9542) (12486.1221 3004.1985)
      (12488.7634 3004.5496) (12491.4046 3005.2519) (12493.3282 3006.3206) (12494.0458 3007.6336) (12493.3282 3008.9466)
      (12491.4046 3010.0153) (12488.7634 3010.7176) (12486.1221 3011.0687) (12484.1374 3011.313) (12483.2519 3011.771)
      (12483.5573 3012.7023) (12484.7939 3014.2748) (12486.3969 3016.3969) (12487.771 3018.7634) (12488.3969 3020.8855)
      (12487.9695 3022.3206) (12486.5344 3022.7481) (12484.4122 3022.1221) (12482.0458 3020.7481) (12479.9237 3019.145)
      (12478.3511 3017.9084) (12477.4198 3017.6031) (12476.9618 3018.4885) (12476.7176 3020.4733) (12476.3664 3023.1145)
      (12475.6641 3025.7557) (12474.5954 3027.6794) (12473.2824 3028.3969) (12471.9695 3027.6794) (12470.9008 3025.7557)
      (12470.1985 3023.1145) (12469.8473 3020.4733) (12469.6031 3018.4885) (12469.145 3017.6031) (12468.2137 3017.9084)
      (12466.6412 3019.145) (12464.5191 3020.7481) (12462.1527 3022.1221) (12460.0305 3022.7481) (12458.5954 3022.3206)
      (12458.1679 3020.8855) (12458.7939 3018.7634) (12460.1679 3016.3969) (12461.771 3014.2748) (12463.0076 3012.7023)
      (12463.313 3011.771) (12462.4275 3011.313) (12460.4427 3011.0687) (12457.8015 3010.7176) (12455.1603 3010.0153)
      (12453.2366 3008.9466)
    ))
    ; P3594 -- see feature_dimensions_mm.csv
    ("06_ORNAMENT" 1 (
      (12452.5191 2900.7634) (12453.2366 2899.4504) (12455.1603 2898.3817) (12457.8015 2897.6794) (12460.4427 2897.3282)
      (12462.4275 2897.084) (12463.313 2896.626) (12463.0076 2895.6947) (12461.771 2894.1221) (12460.1679 2892.0)
      (12458.7939 2889.6336) (12458.1679 2887.5115) (12458.5954 2886.0763) (12460.0305 2885.6489) (12462.1527 2886.2748)
      (12464.5191 2887.6489) (12466.6412 2889.2519) (12468.2137 2890.4885) (12469.145 2890.7939) (12469.6031 2889.9084)
      (12469.8473 2887.9237) (12470.1985 2885.2824) (12470.9008 2882.6412) (12471.9695 2880.7176) (12473.2824 2880.0)
      (12474.5954 2880.7176) (12475.6641 2882.6412) (12476.3664 2885.2824) (12476.7176 2887.9237) (12476.9618 2889.9084)
      (12477.4198 2890.7939) (12478.3511 2890.4885) (12479.9237 2889.2519) (12482.0458 2887.6489) (12484.4122 2886.2748)
      (12486.5344 2885.6489) (12487.9695 2886.0763) (12488.3969 2887.5115) (12487.771 2889.6336) (12486.3969 2892.0)
      (12484.7939 2894.1221) (12483.5573 2895.6947) (12483.2519 2896.626) (12484.1374 2897.084) (12486.1221 2897.3282)
      (12488.7634 2897.6794) (12491.4046 2898.3817) (12493.3282 2899.4504) (12494.0458 2900.7634) (12493.3282 2902.0763)
      (12491.4046 2903.145) (12488.7634 2903.8473) (12486.1221 2904.1985) (12484.1374 2904.4427) (12483.2519 2904.9008)
      (12483.5573 2905.8321) (12484.7939 2907.4046) (12486.3969 2909.5267) (12487.771 2911.8931) (12488.3969 2914.0153)
      (12487.9695 2915.4504) (12486.5344 2915.8779) (12484.4122 2915.2519) (12482.0458 2913.8779) (12479.9237 2912.2748)
      (12478.3511 2911.0382) (12477.4198 2910.7328) (12476.9618 2911.6183) (12476.7176 2913.6031) (12476.3664 2916.2443)
      (12475.6641 2918.8855) (12474.5954 2920.8092) (12473.2824 2921.5267) (12471.9695 2920.8092) (12470.9008 2918.8855)
      (12470.1985 2916.2443) (12469.8473 2913.6031) (12469.6031 2911.6183) (12469.145 2910.7328) (12468.2137 2911.0382)
      (12466.6412 2912.2748) (12464.5191 2913.8779) (12462.1527 2915.2519) (12460.0305 2915.8779) (12458.5954 2915.4504)
      (12458.1679 2914.0153) (12458.7939 2911.8931) (12460.1679 2909.5267) (12461.771 2907.4046) (12463.0076 2905.8321)
      (12463.313 2904.9008) (12462.4275 2904.4427) (12460.4427 2904.1985) (12457.8015 2903.8473) (12455.1603 2903.145)
      (12453.2366 2902.0763)
    ))
    ; P3595 -- see feature_dimensions_mm.csv
    ("06_ORNAMENT" 1 (
      (12467.1756 3007.6336) (12467.6336 3005.2977) (12468.9618 3003.313) (12470.9466 3001.9847) (12473.2824 3001.5267)
      (12475.6183 3001.9847) (12477.6031 3003.313) (12478.9313 3005.2977) (12479.3893 3007.6336) (12478.9313 3009.9695)
      (12477.6031 3011.9542) (12475.6183 3013.2824) (12473.2824 3013.7405) (12470.9466 3013.2824) (12468.9618 3011.9542)
      (12467.6336 3009.9695)
    ))
    ; P3596 -- see feature_dimensions_mm.csv
    ("06_ORNAMENT" 1 (
      (12467.1756 2900.7634) (12467.6336 2898.4275) (12468.9618 2896.4427) (12470.9466 2895.1145) (12473.2824 2894.6565)
      (12475.6183 2895.1145) (12477.6031 2896.4427) (12478.9313 2898.4275) (12479.3893 2900.7634) (12478.9313 2903.0992)
      (12477.6031 2905.084) (12475.6183 2906.4122) (12473.2824 2906.8702) (12470.9466 2906.4122) (12468.9618 2905.084)
      (12467.6336 2903.0992)
    ))
    ; P3597 -- see feature_dimensions_mm.csv
    ("06_ORNAMENT" 1 (
      (12488.3511 5246.3359) (12488.6107 5239.8779) (12490.0305 5232.9466) (12492.5649 5225.6947) (12496.1374 5218.3206)
      (12500.687 5210.9924) (12506.0916 5203.8931) (12512.2137 5197.1908) (12518.916 5191.0687) (12526.0153 5185.6641)
      (12533.3435 5181.1145) (12540.7176 5177.542) (12547.9695 5175.0076) (12554.9008 5173.6031) (12561.3588 5173.3282)
      (12567.1756 5174.229) (12572.2137 5176.2595) (12576.3359 5179.3893) (12579.4656 5183.5115) (12581.4962 5188.5496)
      (12582.3969 5194.3664) (12582.1221 5200.8244) (12580.7176 5207.7557) (12578.1832 5215.0076) (12574.6107 5222.3817)
      (12570.0611 5229.7099) (12564.6565 5236.8092) (12558.5344 5243.5115) (12551.8321 5249.6336) (12544.7328 5255.0382)
      (12537.4046 5259.5878) (12530.0305 5263.1603) (12522.7786 5265.6947) (12515.8473 5267.1145) (12509.3893 5267.374)
      (12503.5725 5266.4733) (12498.5344 5264.4427) (12494.4122 5261.313) (12491.2824 5257.1908) (12489.2519 5252.1527)
    ))
    ; P3598 -- see feature_dimensions_mm.csv
    ("06_ORNAMENT" 1 (
      (12488.3511 4784.1985) (12489.2519 4778.3817) (12491.2824 4773.3435) (12494.4122 4769.2214) (12498.5344 4766.0916)
      (12503.5725 4764.0611) (12509.3893 4763.1603) (12515.8473 4763.4198) (12522.7786 4764.8397) (12530.0305 4767.374)
      (12537.4046 4770.9466) (12544.7328 4775.4962) (12551.8321 4780.9008) (12558.5344 4787.0229) (12564.6565 4793.7252)
      (12570.0611 4800.8244) (12574.6107 4808.1527) (12578.1832 4815.5267) (12580.7176 4822.7786) (12582.1221 4829.7099)
      (12582.3969 4836.1679) (12581.4962 4841.9847) (12579.4656 4847.0229) (12576.3359 4851.145) (12572.2137 4854.2748)
      (12567.1756 4856.3053) (12561.3588 4857.2061) (12554.9008 4856.9313) (12547.9695 4855.5267) (12540.7176 4852.9924)
      (12533.3435 4849.4198) (12526.0153 4844.8702) (12518.916 4839.4656) (12512.2137 4833.3435) (12506.0916 4826.6412)
      (12500.687 4819.542) (12496.1374 4812.2137) (12492.5649 4804.8397) (12490.0305 4797.5878) (12488.6107 4790.6565)
    ))
    ; P3599 -- see feature_dimensions_mm.csv
    ("06_ORNAMENT" 1 (
      (12488.3511 4650.916) (12488.6107 4644.458) (12490.0305 4637.5267) (12492.5649 4630.2748) (12496.1374 4622.9008)
      (12500.687 4615.5725) (12506.0916 4608.4733) (12512.2137 4601.771) (12518.916 4595.6489) (12526.0153 4590.2443)
      (12533.3435 4585.6947) (12540.7176 4582.1221) (12547.9695 4579.5878) (12554.9008 4578.1832) (12561.3588 4577.9084)
      (12567.1756 4578.8092) (12572.2137 4580.8397) (12576.3359 4583.9695) (12579.4656 4588.0916) (12581.4962 4593.1298)
      (12582.3969 4598.9466) (12582.1221 4605.4046) (12580.7176 4612.3359) (12578.1832 4619.5878) (12574.6107 4626.9618)
      (12570.0611 4634.2901) (12564.6565 4641.3893) (12558.5344 4648.0916) (12551.8321 4654.2137) (12544.7328 4659.6183)
      (12537.4046 4664.1679) (12530.0305 4667.7405) (12522.7786 4670.2748) (12515.8473 4671.6947) (12509.3893 4671.9542)
      (12503.5725 4671.0534) (12498.5344 4669.0229) (12494.4122 4665.8931) (12491.2824 4661.771) (12489.2519 4656.7328)
    ))
    ; P3600 -- see feature_dimensions_mm.csv
    ("06_ORNAMENT" 1 (
      (12488.3511 4188.7786) (12489.2519 4182.9618) (12491.2824 4177.9237) (12494.4122 4173.8015) (12498.5344 4170.6718)
      (12503.5725 4168.6412) (12509.3893 4167.7405) (12515.8473 4168.0) (12522.7786 4169.4198) (12530.0305 4171.9542)
      (12537.4046 4175.5267) (12544.7328 4180.0763) (12551.8321 4185.4809) (12558.5344 4191.6031) (12564.6565 4198.3053)
      (12570.0611 4205.4046) (12574.6107 4212.7328) (12578.1832 4220.1069) (12580.7176 4227.3588) (12582.1221 4234.2901)
      (12582.3969 4240.7481) (12581.4962 4246.5649) (12579.4656 4251.6031) (12576.3359 4255.7252) (12572.2137 4258.855)
      (12567.1756 4260.8855) (12561.3588 4261.7863) (12554.9008 4261.5115) (12547.9695 4260.1069) (12540.7176 4257.5725)
      (12533.3435 4254.0) (12526.0153 4249.4504) (12518.916 4244.0458) (12512.2137 4237.9237) (12506.0916 4231.2214)
      (12500.687 4224.1221) (12496.1374 4216.7939) (12492.5649 4209.4198) (12490.0305 4202.1679) (12488.6107 4195.2366)
    ))
    ; P3601 -- see feature_dimensions_mm.csv
    ("06_ORNAMENT" 1 (
      (12488.3511 4055.4962) (12488.6107 4049.0382) (12490.0305 4042.1069) (12492.5649 4034.855) (12496.1374 4027.4809)
      (12500.687 4020.1527) (12506.0916 4013.0534) (12512.2137 4006.3511) (12518.916 4000.229) (12526.0153 3994.8244)
      (12533.3435 3990.2748) (12540.7176 3986.7023) (12547.9695 3984.1679) (12554.9008 3982.7634) (12561.3588 3982.4885)
      (12567.1756 3983.3893) (12572.2137 3985.4198) (12576.3359 3988.5496) (12579.4656 3992.6718) (12581.4962 3997.7099)
      (12582.3969 4003.5267) (12582.1221 4009.9847) (12580.7176 4016.916) (12578.1832 4024.1679) (12574.6107 4031.542)
      (12570.0611 4038.8702) (12564.6565 4045.9695) (12558.5344 4052.6718) (12551.8321 4058.7939) (12544.7328 4064.1985)
      (12537.4046 4068.7481) (12530.0305 4072.3206) (12522.7786 4074.855) (12515.8473 4076.2748) (12509.3893 4076.5344)
      (12503.5725 4075.6336) (12498.5344 4073.6031) (12494.4122 4070.4733) (12491.2824 4066.3511) (12489.2519 4061.313)
    ))
    ; P3602 -- see feature_dimensions_mm.csv
    ("06_ORNAMENT" 1 (
      (12498.5344 5117.4809) (12499.771 5109.6947) (12503.3435 5102.6718) (12508.916 5097.0992) (12515.9389 5093.5267)
      (12523.7252 5092.2901) (12531.5115 5093.5267) (12538.5344 5097.0992) (12544.1069 5102.6718) (12547.6794 5109.6947)
      (12548.916 5117.4809) (12547.6794 5125.2672) (12544.1069 5132.2901) (12538.5344 5137.8626) (12531.5115 5141.4351)
      (12523.7252 5142.6718) (12515.9389 5141.4351) (12508.916 5137.8626) (12503.3435 5132.2901) (12499.771 5125.2672)
    ))
    ; P3603 -- see feature_dimensions_mm.csv
    ("06_ORNAMENT" 1 (
      (12498.5344 4913.0534) (12499.771 4905.2672) (12503.3435 4898.2443) (12508.916 4892.6718) (12515.9389 4889.0992)
      (12523.7252 4887.8626) (12531.5115 4889.0992) (12538.5344 4892.6718) (12544.1069 4898.2443) (12547.6794 4905.2672)
      (12548.916 4913.0534) (12547.6794 4920.8397) (12544.1069 4927.8626) (12538.5344 4933.4351) (12531.5115 4937.0076)
      (12523.7252 4938.2443) (12515.9389 4937.0076) (12508.916 4933.4351) (12503.3435 4927.8626) (12499.771 4920.8397)
    ))
    ; P3604 -- see feature_dimensions_mm.csv
    ("06_ORNAMENT" 1 (
      (12498.5344 4522.0611) (12499.771 4514.2748) (12503.3435 4507.2519) (12508.916 4501.6794) (12515.9389 4498.1069)
      (12523.7252 4496.8702) (12531.5115 4498.1069) (12538.5344 4501.6794) (12544.1069 4507.2519) (12547.6794 4514.2748)
      (12548.916 4522.0611) (12547.6794 4529.8473) (12544.1069 4536.8702) (12538.5344 4542.4427) (12531.5115 4546.0153)
      (12523.7252 4547.2519) (12515.9389 4546.0153) (12508.916 4542.4427) (12503.3435 4536.8702) (12499.771 4529.8473)
    ))
    ; P3605 -- see feature_dimensions_mm.csv
    ("06_ORNAMENT" 1 (
      (12498.5344 4317.6336) (12499.771 4309.8473) (12503.3435 4302.8244) (12508.916 4297.2519) (12515.9389 4293.6794)
      (12523.7252 4292.4427) (12531.5115 4293.6794) (12538.5344 4297.2519) (12544.1069 4302.8244) (12547.6794 4309.8473)
      (12548.916 4317.6336) (12547.6794 4325.4198) (12544.1069 4332.4427) (12538.5344 4338.0153) (12531.5115 4341.5878)
      (12523.7252 4342.8244) (12515.9389 4341.5878) (12508.916 4338.0153) (12503.3435 4332.4427) (12499.771 4325.4198)
    ))
    ; P3606 -- see feature_dimensions_mm.csv
    ("06_ORNAMENT" 1 (
      (12498.5344 3926.6412) (12499.771 3918.855) (12503.3435 3911.8321) (12508.916 3906.2595) (12515.9389 3902.687)
      (12523.7252 3901.4504) (12531.5115 3902.687) (12538.5344 3906.2595) (12544.1069 3911.8321) (12547.6794 3918.855)
      (12548.916 3926.6412) (12547.6794 3934.4275) (12544.1069 3941.4504) (12538.5344 3947.0229) (12531.5115 3950.5954)
      (12523.7252 3951.8321) (12515.9389 3950.5954) (12508.916 3947.0229) (12503.3435 3941.4504) (12499.771 3934.4275)
    ))
    ; P3607 -- see feature_dimensions_mm.csv
    ("06_ORNAMENT" 1 (
      (12515.8015 5312.9771) (12516.5191 5307.8473) (12518.6412 5302.855) (12522.1221 5298.1069) (12526.8702 5293.7252)
      (12532.7786 5289.8168) (12539.6794 5286.4885) (12547.4351 5283.8015) (12555.8321 5281.8321) (12564.6718 5280.626)
      (12573.7405 5280.229) (12582.8092 5280.626) (12591.6489 5281.8321) (12600.0458 5283.8015) (12607.8015 5286.4885)
      (12614.7023 5289.8168) (12620.6107 5293.7252) (12625.3588 5298.1069) (12628.8397 5302.855) (12630.9618 5307.8473)
      (12631.6794 5312.9771) (12630.9618 5318.1069) (12628.8397 5323.0992) (12625.3588 5327.8473) (12620.6107 5332.229)
      (12614.7023 5336.1374) (12607.8015 5339.4656) (12600.0458 5342.1527) (12591.6489 5344.1221) (12582.8092 5345.3282)
      (12573.7405 5345.7252) (12564.6718 5345.3282) (12555.8321 5344.1221) (12547.4351 5342.1527) (12539.6794 5339.4656)
      (12532.7786 5336.1374) (12526.8702 5332.229) (12522.1221 5327.8473) (12518.6412 5323.0992) (12516.5191 5318.1069)
    ))
    ; P3608 -- see feature_dimensions_mm.csv
    ("06_ORNAMENT" 1 (
      (12515.8015 4717.5573) (12516.5191 4712.4275) (12518.6412 4707.4351) (12522.1221 4702.687) (12526.8702 4698.3053)
      (12532.7786 4694.3969) (12539.6794 4691.0687) (12547.4351 4688.3817) (12555.8321 4686.4122) (12564.6718 4685.2061)
      (12573.7405 4684.8092) (12582.8092 4685.2061) (12591.6489 4686.4122) (12600.0458 4688.3817) (12607.8015 4691.0687)
      (12614.7023 4694.3969) (12620.6107 4698.3053) (12625.3588 4702.687) (12628.8397 4707.4351) (12630.9618 4712.4275)
      (12631.6794 4717.5573) (12630.9618 4722.687) (12628.8397 4727.6794) (12625.3588 4732.4275) (12620.6107 4736.8092)
      (12614.7023 4740.7176) (12607.8015 4744.0458) (12600.0458 4746.7328) (12591.6489 4748.7023) (12582.8092 4749.9084)
      (12573.7405 4750.3053) (12564.6718 4749.9084) (12555.8321 4748.7023) (12547.4351 4746.7328) (12539.6794 4744.0458)
      (12532.7786 4740.7176) (12526.8702 4736.8092) (12522.1221 4732.4275) (12518.6412 4727.6794) (12516.5191 4722.687)
    ))
    ; P3609 -- see feature_dimensions_mm.csv
    ("06_ORNAMENT" 1 (
      (12515.8015 4122.1374) (12516.5191 4117.0076) (12518.6412 4112.0153) (12522.1221 4107.2672) (12526.8702 4102.8855)
      (12532.7786 4098.9771) (12539.6794 4095.6489) (12547.4351 4092.9618) (12555.8321 4090.9924) (12564.6718 4089.7863)
      (12573.7405 4089.3893) (12582.8092 4089.7863) (12591.6489 4090.9924) (12600.0458 4092.9618) (12607.8015 4095.6489)
      (12614.7023 4098.9771) (12620.6107 4102.8855) (12625.3588 4107.2672) (12628.8397 4112.0153) (12630.9618 4117.0076)
      (12631.6794 4122.1374) (12630.9618 4127.2672) (12628.8397 4132.2595) (12625.3588 4137.0076) (12620.6107 4141.3893)
      (12614.7023 4145.2977) (12607.8015 4148.626) (12600.0458 4151.313) (12591.6489 4153.2824) (12582.8092 4154.4885)
      (12573.7405 4154.8855) (12564.6718 4154.4885) (12555.8321 4153.2824) (12547.4351 4151.313) (12539.6794 4148.626)
      (12532.7786 4145.2977) (12526.8702 4141.3893) (12522.1221 4137.0076) (12518.6412 4132.2595) (12516.5191 4127.2672)
    ))
    ; P3610 -- see feature_dimensions_mm.csv
    ("06_ORNAMENT" 1 (
      (12519.084 5969.4656) (12550.5496 5968.9924) (12583.8321 5971.3435) (12618.4885 5976.2595) (12654.0611 5983.4656)
      (12690.1221 5992.687) (12726.1832 6003.6641) (12761.8473 6016.1069) (12796.626 6029.771) (12830.0763 6044.3817)
      (12861.771 6059.6641) (12891.2366 6075.3435) (12899.9389 6080.4885) (12896.626 6077.5267) (12889.1298 6069.374)
      (12882.8244 6060.7786) (12877.8626 6051.9084) (12873.2977 6041.8779) (12868.5496 6030.1985) (12864.3664 6017.542)
      (12861.4809 6004.5802) (12860.6412 5992.0) (12862.5954 5980.4885) (12868.0916 5970.7176) (12877.8626 5963.3588)
      (12894.9313 5958.4275) (12919.8931 5955.2519) (12949.8321 5953.5573) (12981.8473 5953.0534) (13013.0229 5953.4656)
      (13040.458 5954.4885) (13061.2672 5955.8473) (13072.5191 5957.2519) (13073.0534 5958.9771) (13065.145 5961.4046)
      (13051.0229 5964.4275) (13032.9466 5967.9389) (13013.1603 5971.8321) (12993.9237 5976.0) (12977.4962 5980.3359)
      (12966.1069 5984.7328) (12958.8092 5989.4046) (12953.0229 5994.5649) (12948.6412 6000.0458) (12945.5115 6005.7252)
      (12943.4809 6011.4504) (12942.4427 6017.084) (12942.2443 6022.4733) (12942.7481 6027.4809) (12944.2748 6032.3511)
      (12947.084 6037.3435) (12950.9771 6042.2901) (12955.7252 6047.0382) (12961.1298 6051.4504) (12966.9618 6055.3588)
      (12973.0229 6058.6107) (12979.084 6061.0687) (12986.0916 6062.687) (12994.6107 6063.5878) (13003.9847 6063.8779)
      (13013.4809 6063.6489) (13022.3969 6062.9924) (13030.0611 6062.0305) (13035.7557 6060.855) (13038.7786 6059.542)
      (13038.3206 6057.9847) (13034.687 6056.0458) (13028.8855 6053.771) (13021.9084 6051.2366) (13014.7786 6048.5038)
      (13008.4885 6045.6183) (13004.0458 6042.6718) (13002.4427 6039.6947) (13003.4962 6036.3359) (13006.1527 6032.3969)
      (13010.1679 6028.1374) (13015.2519 6023.8473) (13021.1908 6019.8321) (13027.6947 6016.3664) (13034.5038 6013.7252)
      (13041.374 6012.2137) (13048.9771 6011.771) (13057.8626 6012.1069) (13067.542 6013.145) (13077.542 6014.7939)
      (13087.4198 6016.9771) (13096.6718 6019.6183) (13104.8397 6022.6412) (13111.4504 6025.9542) (13117.1145 6029.8168)
      (13122.5344 6034.4275) (13127.4046 6039.6031) (13131.4046 6045.1298) (13134.1985 6050.8397) (13135.4809 6056.5496)
      (13134.916 6062.0611) (13132.2137 6067.1756) (13126.9466 6072.1985) (13119.2366 6077.4504) (13109.5878 6082.7328)
      (13098.4733 6087.8779) (13086.3817 6092.7328) (13073.8168 6097.1298) (13061.2519 6100.8702) (13049.1603 6103.8168)
      (13036.9313 6106.1985) (13023.8168 6108.3053) (13010.1527 6109.9695) (12996.2748 6111.0687) (12982.5191 6111.4504)
      (12969.2366 6110.9771) (12956.7176 6109.4962) (12945.3435 6106.8702) (12937.3588 6103.9695) (12941.7099 6106.855)
      (12961.8321 6122.1374) (12933.9847 6120.8855) (12903.6031 6117.9237) (12871.1756 6113.313) (12847.6794 6109.0382)
      (12849.4809 6110.7634) (12853.771 6115.9389) (12857.2977 6121.4656) (12859.771 6127.1756) (12860.9008 6132.8855)
      (12860.4122 6138.3969) (12858.0153 6143.5115) (12853.3588 6148.5344) (12846.5649 6153.7863) (12838.0458 6159.0687)
      (12828.2443 6164.2137) (12817.5878 6169.0687) (12806.4885 6173.4656) (12795.3893 6177.2061) (12784.7328 6180.1527)
      (12773.9389 6182.5344) (12762.3664 6184.6412) (12750.3206 6186.3053) (12738.0763 6187.4046) (12725.9389 6187.7863)
      (12714.1985 6187.313) (12703.1756 6185.8321) (12693.1298 6183.2061) (12683.7405 6179.3435) (12674.5954 6174.3359)
      (12665.8321 6168.3206) (12657.6336 6161.4504) (12650.1527 6153.8626) (12643.542 6145.7099) (12637.9695 6137.1145)
      (12633.5878 6128.2443) (12629.5573 6118.2137) (12625.374 6106.5344) (12621.6794 6093.8779) (12619.1298 6080.916)
      (12618.3969 6068.3359) (12620.1221 6056.8244) (12624.9618 6047.0534) (12631.771 6041.2519) (12627.8168 6039.4962)
      (12596.5954 6023.6794) (12567.7405 6006.687) (12541.7405 5988.5954)
    ))
    ; P3611 -- see feature_dimensions_mm.csv
    ("06_ORNAMENT" 1 (
      (12525.1908 7374.0458) (12526.5496 7371.5267) (12530.2595 7369.4809) (12535.2977 7368.1527) (12540.3511 7367.4656)
      (12544.1374 7367.0076) (12545.8168 7366.1527) (12545.2214 7364.3511) (12542.8855 7361.3435) (12539.8015 7357.2824)
      (12537.1756 7352.7786) (12536.0 7348.7176) (12536.8244 7345.9847) (12539.5573 7345.1603) (12543.6183 7346.3359)
      (12548.1221 7348.9618) (12552.1832 7352.0458) (12555.1908 7354.3817) (12556.9924 7354.9771) (12557.8473 7353.2977)
      (12558.3053 7349.5115) (12559.0076 7344.458) (12560.3206 7339.4198) (12562.3664 7335.7099) (12564.8855 7334.3511)
      (12567.4046 7335.7099) (12569.4504 7339.4198) (12570.7786 7344.458) (12571.4656 7349.5115) (12571.9237 7353.2977)
      (12572.7786 7354.9771) (12574.5802 7354.3817) (12577.5878 7352.0458) (12581.6489 7348.9618) (12586.1527 7346.3359)
      (12590.2137 7345.1603) (12592.9466 7345.9847) (12593.771 7348.7176) (12592.5954 7352.7786) (12589.9695 7357.2824)
      (12586.8855 7361.3435) (12584.5496 7364.3511) (12583.9542 7366.1527) (12585.6336 7367.0076) (12589.4198 7367.4656)
      (12594.4733 7368.1527) (12599.5115 7369.4809) (12603.2214 7371.5267) (12604.5802 7374.0458) (12603.2214 7376.5649)
      (12599.5115 7378.6107) (12594.4733 7379.9237) (12589.4198 7380.626) (12585.6336 7381.084) (12583.9542 7381.9389)
      (12584.5496 7383.7405) (12586.8855 7386.7481) (12589.9695 7390.8092) (12592.5954 7395.313) (12593.771 7399.374)
      (12592.9466 7402.1069) (12590.2137 7402.9313) (12586.1527 7401.7557) (12581.6489 7399.1298) (12577.5878 7396.0458)
      (12574.5802 7393.7099) (12572.7786 7393.1145) (12571.9237 7394.7939) (12571.4656 7398.5802) (12570.7786 7403.6336)
      (12569.4504 7408.6718) (12567.4046 7412.3817) (12564.8855 7413.7405) (12562.3664 7412.3817) (12560.3206 7408.6718)
      (12559.0076 7403.6336) (12558.3053 7398.5802) (12557.8473 7394.7939) (12556.9924 7393.1145) (12555.1908 7393.7099)
      (12552.1832 7396.0458) (12548.1221 7399.1298) (12543.6183 7401.7557) (12539.5573 7402.9313) (12536.8244 7402.1069)
      (12536.0 7399.374) (12537.1756 7395.313) (12539.8015 7390.8092) (12542.8855 7386.7481) (12545.2214 7383.7405)
      (12545.8168 7381.9389) (12544.1374 7381.084) (12540.3511 7380.626) (12535.2977 7379.9237) (12530.2595 7378.6107)
      (12526.5496 7376.5649)
    ))
    ; P3612 -- see feature_dimensions_mm.csv
    ("06_ORNAMENT" 1 (
      (12525.1908 7206.1069) (12526.5496 7203.5878) (12530.2595 7201.542) (12535.2977 7200.2137) (12540.3511 7199.5267)
      (12544.1374 7199.0687) (12545.8168 7198.2137) (12545.2214 7196.4122) (12542.8855 7193.4046) (12539.8015 7189.3435)
      (12537.1756 7184.8397) (12536.0 7180.7786) (12536.8244 7178.0458) (12539.5573 7177.2214) (12543.6183 7178.3969)
      (12548.1221 7181.0229) (12552.1832 7184.1069) (12555.1908 7186.4427) (12556.9924 7187.0382) (12557.8473 7185.3588)
      (12558.3053 7181.5725) (12559.0076 7176.5191) (12560.3206 7171.4809) (12562.3664 7167.771) (12564.8855 7166.4122)
      (12567.4046 7167.771) (12569.4504 7171.4809) (12570.7786 7176.5191) (12571.4656 7181.5725) (12571.9237 7185.3588)
      (12572.7786 7187.0382) (12574.5802 7186.4427) (12577.5878 7184.1069) (12581.6489 7181.0229) (12586.1527 7178.3969)
      (12590.2137 7177.2214) (12592.9466 7178.0458) (12593.771 7180.7786) (12592.5954 7184.8397) (12589.9695 7189.3435)
      (12586.8855 7193.4046) (12584.5496 7196.4122) (12583.9542 7198.2137) (12585.6336 7199.0687) (12589.4198 7199.5267)
      (12594.4733 7200.2137) (12599.5115 7201.542) (12603.2214 7203.5878) (12604.5802 7206.1069) (12603.2214 7208.626)
      (12599.5115 7210.6718) (12594.4733 7211.9847) (12589.4198 7212.687) (12585.6336 7213.145) (12583.9542 7214.0)
      (12584.5496 7215.8015) (12586.8855 7218.8092) (12589.9695 7222.8702) (12592.5954 7227.374) (12593.771 7231.4351)
      (12592.9466 7234.1679) (12590.2137 7234.9924) (12586.1527 7233.8168) (12581.6489 7231.1908) (12577.5878 7228.1069)
      (12574.5802 7225.771) (12572.7786 7225.1756) (12571.9237 7226.855) (12571.4656 7230.6412) (12570.7786 7235.6947)
      (12569.4504 7240.7328) (12567.4046 7244.4427) (12564.8855 7245.8015) (12562.3664 7244.4427) (12560.3206 7240.7328)
      (12559.0076 7235.6947) (12558.3053 7230.6412) (12557.8473 7226.855) (12556.9924 7225.1756) (12555.1908 7225.771)
      (12552.1832 7228.1069) (12548.1221 7231.1908) (12543.6183 7233.8168) (12539.5573 7234.9924) (12536.8244 7234.1679)
      (12536.0 7231.4351) (12537.1756 7227.374) (12539.8015 7222.8702) (12542.8855 7218.8092) (12545.2214 7215.8015)
      (12545.8168 7214.0) (12544.1374 7213.145) (12540.3511 7212.687) (12535.2977 7211.9847) (12530.2595 7210.6718)
      (12526.5496 7208.626)
    ))
    ; P3613 -- see feature_dimensions_mm.csv
    ("06_ORNAMENT" 1 (
      (12532.626 5068.6107) (12534.1527 5062.9466) (12538.3053 5058.7939) (12543.9695 5057.2672) (12549.6336 5058.7939)
      (12553.7863 5062.9466) (12555.2977 5068.6107) (12553.7863 5074.2748) (12549.6336 5078.4275) (12543.9695 5079.9389)
      (12538.3053 5078.4275) (12534.1527 5074.2748)
    ))
    ; P3614 -- see feature_dimensions_mm.csv
    ("06_ORNAMENT" 1 (
      (12532.626 4961.9237) (12534.1527 4956.2595) (12538.3053 4952.1069) (12543.9695 4950.5954) (12549.6336 4952.1069)
      (12553.7863 4956.2595) (12555.2977 4961.9237) (12553.7863 4967.5878) (12549.6336 4971.7405) (12543.9695 4973.2672)
      (12538.3053 4971.7405) (12534.1527 4967.5878)
    ))
    ; P3615 -- see feature_dimensions_mm.csv
    ("06_ORNAMENT" 1 (
      (12532.626 4366.5038) (12534.1527 4360.8397) (12538.3053 4356.687) (12543.9695 4355.1756) (12549.6336 4356.687)
      (12553.7863 4360.8397) (12555.2977 4366.5038) (12553.7863 4372.1679) (12549.6336 4376.3206) (12543.9695 4377.8473)
      (12538.3053 4376.3206) (12534.1527 4372.1679)
    ))
    ; P3616 -- see feature_dimensions_mm.csv
    ("06_ORNAMENT" 1 (
      (12532.626 3877.771) (12534.1527 3872.1069) (12538.3053 3867.9542) (12543.9695 3866.4275) (12549.6336 3867.9542)
      (12553.7863 3872.1069) (12555.2977 3877.771) (12553.7863 3883.4351) (12549.6336 3887.5878) (12543.9695 3889.0992)
      (12538.3053 3887.5878) (12534.1527 3883.4351)
    ))
    ; P3617 -- see feature_dimensions_mm.csv
    ("06_ORNAMENT" 1 (
      (12540.458 5022.9008) (12540.8702 5020.3206) (12542.0611 5017.8931) (12543.9542 5015.6947) (12546.4122 5013.8626)
      (12549.2519 5012.4122) (12552.2748 5011.3588) (12555.313 5010.6412) (12558.1527 5010.1985) (12560.6718 5009.8779)
      (12562.7634 5009.5573) (12564.3969 5009.084) (12565.5573 5008.3053) (12566.3359 5007.145) (12566.8092 5005.5115)
      (12567.1298 5003.4198) (12567.4504 5000.9008) (12567.8931 4998.0611) (12568.6107 4995.0229) (12569.6641 4992.0)
      (12571.1145 4989.1603) (12572.9466 4986.7023) (12575.145 4984.8092) (12577.5725 4983.6183) (12580.1527 4983.2061)
      (12582.7328 4983.6183) (12585.1603 4984.8092) (12587.3588 4986.7023) (12589.1908 4989.1603) (12590.6412 4992.0)
      (12591.6947 4995.0229) (12592.4122 4998.0611) (12592.855 5000.9008) (12593.1756 5003.4198) (12593.4962 5005.5115)
      (12593.9695 5007.145) (12594.7481 5008.3053) (12595.9084 5009.084) (12597.542 5009.5573) (12599.6336 5009.8779)
      (12602.1527 5010.1985) (12604.9924 5010.6412) (12608.0305 5011.3588) (12611.0534 5012.4122) (12613.8931 5013.8626)
      (12616.3511 5015.6947) (12618.2443 5017.8931) (12619.4351 5020.3206) (12619.8473 5022.9008) (12619.4351 5025.4809)
      (12618.2443 5027.9084) (12616.3511 5030.1069) (12613.8931 5031.9389) (12611.0534 5033.3893) (12608.0305 5034.4427)
      (12604.9924 5035.1603) (12602.1527 5035.6031) (12599.6336 5035.9237) (12597.542 5036.2443) (12595.9084 5036.7176)
      (12594.7481 5037.4962) (12593.9695 5038.6565) (12593.4962 5040.2901) (12593.1756 5042.3817) (12592.855 5044.9008)
      (12592.4122 5047.7405) (12591.6947 5050.7786) (12590.6412 5053.8015) (12589.1908 5056.6412) (12587.3588 5059.0992)
      (12585.1603 5060.9924) (12582.7328 5062.1832) (12580.1527 5062.5954) (12577.5725 5062.1832) (12575.145 5060.9924)
      (12572.9466 5059.0992) (12571.1145 5056.6412) (12569.6641 5053.8015) (12568.6107 5050.7786) (12567.8931 5047.7405)
      (12567.4504 5044.9008) (12567.1298 5042.3817) (12566.8092 5040.2901) (12566.3359 5038.6565) (12565.5573 5037.4962)
      (12564.3969 5036.7176) (12562.7634 5036.2443) (12560.6718 5035.9237) (12558.1527 5035.6031) (12555.313 5035.1603)
      (12552.2748 5034.4427) (12549.2519 5033.3893) (12546.4122 5031.9389) (12543.9542 5030.1069) (12542.0611 5027.9084)
      (12540.8702 5025.4809)
    ))
    ; P3618 -- see feature_dimensions_mm.csv
    ("06_ORNAMENT" 1 (
      (12555.7557 7374.0458) (12556.458 7370.5496) (12558.4275 7367.5878) (12561.3893 7365.6183) (12564.8855 7364.916)
      (12568.3817 7365.6183) (12571.3435 7367.5878) (12573.313 7370.5496) (12574.0153 7374.0458) (12573.313 7377.542)
      (12571.3435 7380.5038) (12568.3817 7382.4733) (12564.8855 7383.1756) (12561.3893 7382.4733) (12558.4275 7380.5038)
      (12556.458 7377.542)
    ))
    ; P3619 -- see feature_dimensions_mm.csv
    ("06_ORNAMENT" 1 (
      (12555.7557 7206.1069) (12556.458 7202.6107) (12558.4275 7199.6489) (12561.3893 7197.6794) (12564.8855 7196.9771)
      (12568.3817 7197.6794) (12571.3435 7199.6489) (12573.313 7202.6107) (12574.0153 7206.1069) (12573.313 7209.6031)
      (12571.3435 7212.5649) (12568.3817 7214.5344) (12564.8855 7215.2366) (12561.3893 7214.5344) (12558.4275 7212.5649)
      (12556.458 7209.6031)
    ))
    ; P3620 -- see feature_dimensions_mm.csv
    ("06_ORNAMENT" 1 (
      (12595.4198 1740.458) (12597.4809 1719.6031) (12603.5573 1699.5573) (12613.4351 1681.084) (12626.7176 1664.8855)
      (12642.916 1651.6031) (12661.3893 1641.7252) (12681.4351 1635.6336) (12702.2901 1633.5878) (12723.145 1635.6336)
      (12743.1908 1641.7252) (12761.6641 1651.6031) (12777.8626 1664.8855) (12791.145 1681.084) (12801.0229 1699.5573)
      (12807.1145 1719.6031) (12809.1603 1740.458) (12807.1145 1761.313) (12801.0229 1781.3588) (12791.145 1799.8321)
      (12777.8626 1816.0305) (12761.6641 1829.313) (12743.1908 1839.1908) (12723.145 1845.2672) (12702.2901 1847.3282)
      (12681.4351 1845.2672) (12661.3893 1839.1908) (12642.916 1829.313) (12626.7176 1816.0305) (12613.4351 1799.8321)
      (12603.5573 1781.3588) (12597.4809 1761.313)
    ))
    ; P3621 -- see feature_dimensions_mm.csv
    ("06_ORNAMENT" 1 (
      (12613.0534 5232.0) (12614.2901 5224.2137) (12617.8626 5217.1908) (12623.4351 5211.6183) (12630.458 5208.0458)
      (12638.2443 5206.8092) (12646.0305 5208.0458) (12653.0534 5211.6183) (12658.626 5217.1908) (12662.1985 5224.2137)
      (12663.4351 5232.0) (12662.1985 5239.7863) (12658.626 5246.8092) (12653.0534 5252.3817) (12646.0305 5255.9542)
      (12638.2443 5257.1908) (12630.458 5255.9542) (12623.4351 5252.3817) (12617.8626 5246.8092) (12614.2901 5239.7863)
    ))
    ; P3622 -- see feature_dimensions_mm.csv
    ("06_ORNAMENT" 1 (
      (12613.0534 4798.5344) (12614.2901 4790.7481) (12617.8626 4783.7252) (12623.4351 4778.1527) (12630.458 4774.5802)
      (12638.2443 4773.3435) (12646.0305 4774.5802) (12653.0534 4778.1527) (12658.626 4783.7252) (12662.1985 4790.7481)
      (12663.4351 4798.5344) (12662.1985 4806.3206) (12658.626 4813.3435) (12653.0534 4818.916) (12646.0305 4822.4885)
      (12638.2443 4823.7252) (12630.458 4822.4885) (12623.4351 4818.916) (12617.8626 4813.3435) (12614.2901 4806.3206)
    ))
    ; P3623 -- see feature_dimensions_mm.csv
    ("06_ORNAMENT" 1 (
      (12613.0534 4636.5802) (12614.2901 4628.7939) (12617.8626 4621.771) (12623.4351 4616.1985) (12630.458 4612.626)
      (12638.2443 4611.3893) (12646.0305 4612.626) (12653.0534 4616.1985) (12658.626 4621.771) (12662.1985 4628.7939)
      (12663.4351 4636.5802) (12662.1985 4644.3664) (12658.626 4651.3893) (12653.0534 4656.9618) (12646.0305 4660.5344)
      (12638.2443 4661.771) (12630.458 4660.5344) (12623.4351 4656.9618) (12617.8626 4651.3893) (12614.2901 4644.3664)
    ))
    ; P3624 -- see feature_dimensions_mm.csv
    ("06_ORNAMENT" 1 (
      (12613.0534 4203.1145) (12614.2901 4195.3282) (12617.8626 4188.3053) (12623.4351 4182.7328) (12630.458 4179.1603)
      (12638.2443 4177.9237) (12646.0305 4179.1603) (12653.0534 4182.7328) (12658.626 4188.3053) (12662.1985 4195.3282)
      (12663.4351 4203.1145) (12662.1985 4210.9008) (12658.626 4217.9237) (12653.0534 4223.4962) (12646.0305 4227.0687)
      (12638.2443 4228.3053) (12630.458 4227.0687) (12623.4351 4223.4962) (12617.8626 4217.9237) (12614.2901 4210.9008)
    ))
    ; P3625 -- see feature_dimensions_mm.csv
    ("06_ORNAMENT" 1 (
      (12613.0534 4041.1603) (12614.2901 4033.374) (12617.8626 4026.3511) (12623.4351 4020.7786) (12630.458 4017.2061)
      (12638.2443 4015.9695) (12646.0305 4017.2061) (12653.0534 4020.7786) (12658.626 4026.3511) (12662.1985 4033.374)
      (12663.4351 4041.1603) (12662.1985 4048.9466) (12658.626 4055.9695) (12653.0534 4061.542) (12646.0305 4065.1145)
      (12638.2443 4066.3511) (12630.458 4065.1145) (12623.4351 4061.542) (12617.8626 4055.9695) (12614.2901 4048.9466)
    ))
    ; P3626 -- see feature_dimensions_mm.csv
    ("06_ORNAMENT" 1 (
      (12618.4427 5125.9389) (12619.9695 5120.2748) (12624.1069 5116.1221) (12629.7863 5114.6107) (12635.4504 5116.1221)
      (12639.6031 5120.2748) (12641.1145 5125.9389) (12639.6031 5131.6183) (12635.4504 5135.7557) (12629.7863 5137.2824)
      (12624.1069 5135.7557) (12619.9695 5131.6183)
    ))
    ; P3627 -- see feature_dimensions_mm.csv
    ("06_ORNAMENT" 1 (
      (12618.4427 4904.5954) (12619.9695 4898.916) (12624.1069 4894.7786) (12629.7863 4893.2519) (12635.4504 4894.7786)
      (12639.6031 4898.916) (12641.1145 4904.5954) (12639.6031 4910.2595) (12635.4504 4914.4122) (12629.7863 4915.9237)
      (12624.1069 4914.4122) (12619.9695 4910.2595)
    ))
    ; P3628 -- see feature_dimensions_mm.csv
    ("06_ORNAMENT" 1 (
      (12618.4427 4530.5191) (12619.9695 4524.855) (12624.1069 4520.7023) (12629.7863 4519.1908) (12635.4504 4520.7023)
      (12639.6031 4524.855) (12641.1145 4530.5191) (12639.6031 4536.1985) (12635.4504 4540.3359) (12629.7863 4541.8626)
      (12624.1069 4540.3359) (12619.9695 4536.1985)
    ))
    ; P3629 -- see feature_dimensions_mm.csv
    ("06_ORNAMENT" 1 (
      (12618.4427 4309.1756) (12619.9695 4303.4962) (12624.1069 4299.3588) (12629.7863 4297.8321) (12635.4504 4299.3588)
      (12639.6031 4303.4962) (12641.1145 4309.1756) (12639.6031 4314.8397) (12635.4504 4318.9924) (12629.7863 4320.5038)
      (12624.1069 4318.9924) (12619.9695 4314.8397)
    ))
    ; P3630 -- see feature_dimensions_mm.csv
    ("06_ORNAMENT" 1 (
      (12618.4427 3935.0992) (12619.9695 3929.4351) (12624.1069 3925.2824) (12629.7863 3923.771) (12635.4504 3925.2824)
      (12639.6031 3929.4351) (12641.1145 3935.0992) (12639.6031 3940.7786) (12635.4504 3944.916) (12629.7863 3946.4427)
      (12624.1069 3944.916) (12619.9695 3940.7786)
    ))
    ; P3631 -- see feature_dimensions_mm.csv
    ("06_ORNAMENT" 1 (
      (12625.9542 2000.0) (12626.9008 1978.5038) (12629.6947 1957.542) (12634.2748 1937.6183) (12640.5344 1919.2366)
      (12648.3053 1902.8397) (12657.4198 1888.8397) (12667.6336 1877.5725) (12678.7023 1869.313) (12690.3511 1864.2901)
      (12702.2901 1862.5954) (12714.229 1864.2901) (12725.8779 1869.313) (12736.9466 1877.5725) (12747.1603 1888.8397)
      (12756.2748 1902.8397) (12764.0458 1919.2366) (12770.3053 1937.6183) (12774.8855 1957.542) (12777.6794 1978.5038)
      (12778.626 2000.0) (12777.6794 2021.4962) (12774.8855 2042.458) (12770.3053 2062.3817) (12764.0458 2080.7634)
      (12756.2748 2097.1603) (12747.1603 2111.1603) (12736.9466 2122.4275) (12725.8779 2130.687) (12714.229 2135.7099)
      (12702.2901 2137.4046) (12690.3511 2135.7099) (12678.7023 2130.687) (12667.6336 2122.4275) (12657.4198 2111.1603)
      (12648.3053 2097.1603) (12640.5344 2080.7634) (12634.2748 2062.3817) (12629.6947 2042.458) (12626.9008 2021.4962)
    ))
    ; P3632 -- see feature_dimensions_mm.csv
    ("06_ORNAMENT" 1 (
      (12625.9542 1740.458) (12627.4198 1725.5725) (12631.771 1711.2519) (12638.8244 1698.0458) (12648.3053 1686.4733)
      (12659.8779 1676.9924) (12673.084 1669.9389) (12687.4046 1665.5878) (12702.2901 1664.1221) (12717.1756 1665.5878)
      (12731.4962 1669.9389) (12744.7023 1676.9924) (12756.2748 1686.4733) (12765.7557 1698.0458) (12772.8092 1711.2519)
      (12777.1603 1725.5725) (12778.626 1740.458) (12777.1603 1755.3435) (12772.8092 1769.6641) (12765.7557 1782.8702)
      (12756.2748 1794.4427) (12744.7023 1803.9237) (12731.4962 1810.9771) (12717.1756 1815.3282) (12702.2901 1816.7939)
      (12687.4046 1815.3282) (12673.084 1810.9771) (12659.8779 1803.9237) (12648.3053 1794.4427) (12638.8244 1782.8702)
      (12631.771 1769.6641) (12627.4198 1755.3435)
    ))
    ; P3633 -- see feature_dimensions_mm.csv
    ("06_ORNAMENT" 1 (
      (12625.9542 1480.916) (12626.9008 1459.4198) (12629.6947 1438.458) (12634.2748 1418.5344) (12640.5344 1400.1527)
      (12648.3053 1383.7557) (12657.4198 1369.7557) (12667.6336 1358.4885) (12678.7023 1350.229) (12690.3511 1345.2061)
      (12702.2901 1343.5115) (12714.229 1345.2061) (12725.8779 1350.229) (12736.9466 1358.4885) (12747.1603 1369.7557)
      (12756.2748 1383.7557) (12764.0458 1400.1527) (12770.3053 1418.5344) (12774.8855 1438.458) (12777.6794 1459.4198)
      (12778.626 1480.916) (12777.6794 1502.4122) (12774.8855 1523.374) (12770.3053 1543.2977) (12764.0458 1561.6794)
      (12756.2748 1578.0763) (12747.1603 1592.0763) (12736.9466 1603.3435) (12725.8779 1611.6031) (12714.229 1616.626)
      (12702.2901 1618.3206) (12690.3511 1616.626) (12678.7023 1611.6031) (12667.6336 1603.3435) (12657.4198 1592.0763)
      (12648.3053 1578.0763) (12640.5344 1561.6794) (12634.2748 1543.2977) (12629.6947 1523.374) (12626.9008 1502.4122)
    ))
    ; P3634 -- see feature_dimensions_mm.csv
    ("06_ORNAMENT" 1 (
      (12664.1221 2198.4733) (12665.9847 2186.6718) (12671.4046 2176.0458) (12679.8626 2167.5878) (12690.4885 2162.1679)
      (12702.2901 2160.3053) (12714.0916 2162.1679) (12724.7176 2167.5878) (12733.1756 2176.0458) (12738.5954 2186.6718)
      (12740.458 2198.4733) (12738.5954 2210.2748) (12733.1756 2220.9008) (12724.7176 2229.3588) (12714.0916 2234.7786)
      (12702.2901 2236.6412) (12690.4885 2234.7786) (12679.8626 2229.3588) (12671.4046 2220.9008) (12665.9847 2210.2748)
    ))
    ; P3635 -- see feature_dimensions_mm.csv
    ("06_ORNAMENT" 1 (
      (12664.1221 1282.4427) (12665.9847 1270.6412) (12671.4046 1260.0153) (12679.8626 1251.5573) (12690.4885 1246.1374)
      (12702.2901 1244.2748) (12714.0916 1246.1374) (12724.7176 1251.5573) (12733.1756 1260.0153) (12738.5954 1270.6412)
      (12740.458 1282.4427) (12738.5954 1294.2443) (12733.1756 1304.8702) (12724.7176 1313.3282) (12714.0916 1318.7481)
      (12702.2901 1320.6107) (12690.4885 1318.7481) (12679.8626 1313.3282) (12671.4046 1304.8702) (12665.9847 1294.2443)
    ))
    ; P3636 -- see feature_dimensions_mm.csv
    ("06_ORNAMENT" 1 (
      (12675.7863 5211.7557) (12677.2977 5206.0916) (12681.4504 5201.9389) (12687.1145 5200.4275) (12692.7786 5201.9389)
      (12696.9313 5206.0916) (12698.458 5211.7557) (12696.9313 5217.4198) (12692.7786 5221.5725) (12687.1145 5223.0992)
      (12681.4504 5221.5725) (12677.2977 5217.4198)
    ))
    ; P3637 -- see feature_dimensions_mm.csv
    ("06_ORNAMENT" 1 (
      (12675.7863 4818.7786) (12677.2977 4813.1145) (12681.4504 4808.9618) (12687.1145 4807.4351) (12692.7786 4808.9618)
      (12696.9313 4813.1145) (12698.458 4818.7786) (12696.9313 4824.4427) (12692.7786 4828.5954) (12687.1145 4830.1069)
      (12681.4504 4828.5954) (12677.2977 4824.4427)
    ))
    ; P3638 -- see feature_dimensions_mm.csv
    ("06_ORNAMENT" 1 (
      (12675.7863 4616.3359) (12677.2977 4610.6718) (12681.4504 4606.5191) (12687.1145 4605.0076) (12692.7786 4606.5191)
      (12696.9313 4610.6718) (12698.458 4616.3359) (12696.9313 4622.0) (12692.7786 4626.1527) (12687.1145 4627.6794)
      (12681.4504 4626.1527) (12677.2977 4622.0)
    ))
    ; P3639 -- see feature_dimensions_mm.csv
    ("06_ORNAMENT" 1 (
      (12675.7863 4223.3588) (12677.2977 4217.6947) (12681.4504 4213.542) (12687.1145 4212.0153) (12692.7786 4213.542)
      (12696.9313 4217.6947) (12698.458 4223.3588) (12696.9313 4229.0229) (12692.7786 4233.1756) (12687.1145 4234.687)
      (12681.4504 4233.1756) (12677.2977 4229.0229)
    ))
    ; P3640 -- see feature_dimensions_mm.csv
    ("06_ORNAMENT" 1 (
      (12675.7863 4020.916) (12677.2977 4015.2519) (12681.4504 4011.0992) (12687.1145 4009.5878) (12692.7786 4011.0992)
      (12696.9313 4015.2519) (12698.458 4020.916) (12696.9313 4026.5802) (12692.7786 4030.7328) (12687.1145 4032.2595)
      (12681.4504 4030.7328) (12677.2977 4026.5802)
    ))
    ; P3641 -- see feature_dimensions_mm.csv
    ("06_ORNAMENT" 1 (
      (12690.3969 6098.8092) (12690.8397 6103.8168) (12692.1832 6108.687) (12694.6718 6113.6794) (12698.0916 6118.626)
      (12702.2901 6123.374) (12707.0534 6127.7863) (12712.1985 6131.6947) (12717.542 6134.9466) (12722.9008 6137.4046)
      (12729.084 6139.0229) (12736.6107 6139.9237) (12744.8702 6140.2137) (12753.2519 6139.9847) (12761.1145 6139.3282)
      (12767.8779 6138.3664) (12772.9008 6137.1908) (12775.5725 6135.8779) (12775.1603 6134.3206) (12771.9542 6132.3817)
      (12766.8397 6130.1069) (12760.687 6127.5725) (12754.3969 6124.8397) (12748.8397 6121.9542) (12744.916 6119.0076)
      (12743.5115 6116.0305) (12744.4427 6112.6718) (12746.7786 6108.7328) (12750.3206 6104.4733) (12754.8244 6100.1832)
      (12760.0458 6096.1679) (12765.7863 6092.7023) (12769.6794 6090.9924) (12766.4427 6090.1527) (12730.7023 6079.4962)
      (12701.2977 6069.4962) (12699.9084 6070.9008) (12696.0458 6076.3817) (12693.2672 6082.0611) (12691.4962 6087.7863)
      (12690.5649 6093.4198)
    ))
    ; P3642 -- see feature_dimensions_mm.csv
    ("06_ORNAMENT" 1 (
      (12695.9237 5312.9771) (12697.4351 5307.313) (12701.5878 5303.1603) (12707.2519 5301.6336) (12712.916 5303.1603)
      (12717.0687 5307.313) (12718.5954 5312.9771) (12717.0687 5318.6412) (12712.916 5322.7939) (12707.2519 5324.3053)
      (12701.5878 5322.7939) (12697.4351 5318.6412)
    ))
    ; P3643 -- see feature_dimensions_mm.csv
    ("06_ORNAMENT" 1 (
      (12695.9237 4717.5573) (12697.4351 4711.8931) (12701.5878 4707.7405) (12707.2519 4706.2137) (12712.916 4707.7405)
      (12717.0687 4711.8931) (12718.5954 4717.5573) (12717.0687 4723.2214) (12712.916 4727.374) (12707.2519 4728.8855)
      (12701.5878 4727.374) (12697.4351 4723.2214)
    ))
    ; P3644 -- see feature_dimensions_mm.csv
    ("06_ORNAMENT" 1 (
      (12695.9237 4122.1374) (12697.4351 4116.4733) (12701.5878 4112.3206) (12707.2519 4110.7939) (12712.916 4112.3206)
      (12717.0687 4116.4733) (12718.5954 4122.1374) (12717.0687 4127.8015) (12712.916 4131.9542) (12707.2519 4133.4656)
      (12701.5878 4131.9542) (12697.4351 4127.8015)
    ))
    ; P3645 -- see feature_dimensions_mm.csv
    ("06_ORNAMENT" 1 (
      (12725.9542 5275.0687) (12727.1756 5268.9313) (12730.6565 5263.7252) (12735.8473 5260.2595) (12741.9847 5259.0382)
      (12748.1221 5260.2595) (12753.313 5263.7252) (12756.7939 5268.9313) (12758.0153 5275.0687) (12756.7939 5281.2061)
      (12753.313 5286.3969) (12748.1221 5289.8779) (12741.9847 5291.0992) (12735.8473 5289.8779) (12730.6565 5286.3969)
      (12727.1756 5281.2061)
    ))
    ; P3646 -- see feature_dimensions_mm.csv
    ("06_ORNAMENT" 1 (
      (12725.9542 5198.7328) (12727.1756 5192.5954) (12730.6565 5187.3893) (12735.8473 5183.9237) (12741.9847 5182.7023)
      (12748.1221 5183.9237) (12753.313 5187.3893) (12756.7939 5192.5954) (12758.0153 5198.7328) (12756.7939 5204.8702)
      (12753.313 5210.0611) (12748.1221 5213.542) (12741.9847 5214.7634) (12735.8473 5213.542) (12730.6565 5210.0611)
      (12727.1756 5204.8702)
    ))
    ; P3647 -- see feature_dimensions_mm.csv
    ("06_ORNAMENT" 1 (
      (12725.9542 5122.3969) (12727.1756 5116.2595) (12730.6565 5111.0534) (12735.8473 5107.5878) (12741.9847 5106.3664)
      (12748.1221 5107.5878) (12753.313 5111.0534) (12756.7939 5116.2595) (12758.0153 5122.3969) (12756.7939 5128.5344)
      (12753.313 5133.7252) (12748.1221 5137.2061) (12741.9847 5138.4275) (12735.8473 5137.2061) (12730.6565 5133.7252)
      (12727.1756 5128.5344)
    ))
    ; P3648 -- see feature_dimensions_mm.csv
    ("06_ORNAMENT" 1 (
      (12725.9542 5046.0611) (12727.1756 5039.9237) (12730.6565 5034.7176) (12735.8473 5031.2519) (12741.9847 5030.0305)
      (12748.1221 5031.2519) (12753.313 5034.7176) (12756.7939 5039.9237) (12758.0153 5046.0611) (12756.7939 5052.1985)
      (12753.313 5057.3893) (12748.1221 5060.8702) (12741.9847 5062.0916) (12735.8473 5060.8702) (12730.6565 5057.3893)
      (12727.1756 5052.1985)
    ))
    ; P3649 -- see feature_dimensions_mm.csv
    ("06_ORNAMENT" 1 (
      (12725.9542 4969.7252) (12727.1756 4963.5878) (12730.6565 4958.3817) (12735.8473 4954.916) (12741.9847 4953.6947)
      (12748.1221 4954.916) (12753.313 4958.3817) (12756.7939 4963.5878) (12758.0153 4969.7252) (12756.7939 4975.8626)
      (12753.313 4981.0534) (12748.1221 4984.5344) (12741.9847 4985.7557) (12735.8473 4984.5344) (12730.6565 4981.0534)
      (12727.1756 4975.8626)
    ))
    ; P3650 -- see feature_dimensions_mm.csv
    ("06_ORNAMENT" 1 (
      (12725.9542 4893.3893) (12727.1756 4887.2519) (12730.6565 4882.0458) (12735.8473 4878.5802) (12741.9847 4877.3588)
      (12748.1221 4878.5802) (12753.313 4882.0458) (12756.7939 4887.2519) (12758.0153 4893.3893) (12756.7939 4899.5267)
      (12753.313 4904.7176) (12748.1221 4908.1985) (12741.9847 4909.4198) (12735.8473 4908.1985) (12730.6565 4904.7176)
      (12727.1756 4899.5267)
    ))
    ; P3651 -- see feature_dimensions_mm.csv
    ("06_ORNAMENT" 1 (
      (12725.9542 4817.0534) (12727.1756 4810.916) (12730.6565 4805.7099) (12735.8473 4802.2443) (12741.9847 4801.0229)
      (12748.1221 4802.2443) (12753.313 4805.7099) (12756.7939 4810.916) (12758.0153 4817.0534) (12756.7939 4823.1908)
      (12753.313 4828.3817) (12748.1221 4831.8626) (12741.9847 4833.084) (12735.8473 4831.8626) (12730.6565 4828.3817)
      (12727.1756 4823.1908)
    ))
    ; P3652 -- see feature_dimensions_mm.csv
    ("06_ORNAMENT" 1 (
      (12725.9542 4664.3817) (12727.1756 4658.2443) (12730.6565 4653.0382) (12735.8473 4649.5725) (12741.9847 4648.3511)
      (12748.1221 4649.5725) (12753.313 4653.0382) (12756.7939 4658.2443) (12758.0153 4664.3817) (12756.7939 4670.5191)
      (12753.313 4675.7099) (12748.1221 4679.1908) (12741.9847 4680.4122) (12735.8473 4679.1908) (12730.6565 4675.7099)
      (12727.1756 4670.5191)
    ))
    ; P3653 -- see feature_dimensions_mm.csv
    ("06_ORNAMENT" 1 (
      (12725.9542 4588.0458) (12727.1756 4581.9084) (12730.6565 4576.7023) (12735.8473 4573.2366) (12741.9847 4572.0153)
      (12748.1221 4573.2366) (12753.313 4576.7023) (12756.7939 4581.9084) (12758.0153 4588.0458) (12756.7939 4594.1832)
      (12753.313 4599.374) (12748.1221 4602.855) (12741.9847 4604.0763) (12735.8473 4602.855) (12730.6565 4599.374)
      (12727.1756 4594.1832)
    ))
    ; P3654 -- see feature_dimensions_mm.csv
    ("06_ORNAMENT" 1 (
      (12725.9542 4511.7099) (12727.1756 4505.5725) (12730.6565 4500.3664) (12735.8473 4496.9008) (12741.9847 4495.6794)
      (12748.1221 4496.9008) (12753.313 4500.3664) (12756.7939 4505.5725) (12758.0153 4511.7099) (12756.7939 4517.8473)
      (12753.313 4523.0382) (12748.1221 4526.5191) (12741.9847 4527.7405) (12735.8473 4526.5191) (12730.6565 4523.0382)
      (12727.1756 4517.8473)
    ))
    ; P3655 -- see feature_dimensions_mm.csv
    ("06_ORNAMENT" 1 (
      (12725.9542 4359.0382) (12727.1756 4352.9008) (12730.6565 4347.6947) (12735.8473 4344.229) (12741.9847 4343.0076)
      (12748.1221 4344.229) (12753.313 4347.6947) (12756.7939 4352.9008) (12758.0153 4359.0382) (12756.7939 4365.1756)
      (12753.313 4370.3664) (12748.1221 4373.8473) (12741.9847 4375.0687) (12735.8473 4373.8473) (12730.6565 4370.3664)
      (12727.1756 4365.1756)
    ))
    ; P3656 -- see feature_dimensions_mm.csv
    ("06_ORNAMENT" 1 (
      (12725.9542 4282.7023) (12727.1756 4276.5649) (12730.6565 4271.3588) (12735.8473 4267.8931) (12741.9847 4266.6718)
      (12748.1221 4267.8931) (12753.313 4271.3588) (12756.7939 4276.5649) (12758.0153 4282.7023) (12756.7939 4288.8397)
      (12753.313 4294.0305) (12748.1221 4297.5115) (12741.9847 4298.7328) (12735.8473 4297.5115) (12730.6565 4294.0305)
      (12727.1756 4288.8397)
    ))
    ; P3657 -- see feature_dimensions_mm.csv
    ("06_ORNAMENT" 1 (
      (12725.9542 4206.3664) (12727.1756 4200.229) (12730.6565 4195.0229) (12735.8473 4191.5573) (12741.9847 4190.3359)
      (12748.1221 4191.5573) (12753.313 4195.0229) (12756.7939 4200.229) (12758.0153 4206.3664) (12756.7939 4212.5038)
      (12753.313 4217.6947) (12748.1221 4221.1756) (12741.9847 4222.3969) (12735.8473 4221.1756) (12730.6565 4217.6947)
      (12727.1756 4212.5038)
    ))
    ; P3658 -- see feature_dimensions_mm.csv
    ("06_ORNAMENT" 1 (
      (12725.9542 4053.6947) (12727.1756 4047.5573) (12730.6565 4042.3511) (12735.8473 4038.8855) (12741.9847 4037.6641)
      (12748.1221 4038.8855) (12753.313 4042.3511) (12756.7939 4047.5573) (12758.0153 4053.6947) (12756.7939 4059.8321)
      (12753.313 4065.0229) (12748.1221 4068.5038) (12741.9847 4069.7252) (12735.8473 4068.5038) (12730.6565 4065.0229)
      (12727.1756 4059.8321)
    ))
    ; P3659 -- see feature_dimensions_mm.csv
    ("06_ORNAMENT" 1 (
      (12725.9542 3977.3588) (12727.1756 3971.2214) (12730.6565 3966.0153) (12735.8473 3962.5496) (12741.9847 3961.3282)
      (12748.1221 3962.5496) (12753.313 3966.0153) (12756.7939 3971.2214) (12758.0153 3977.3588) (12756.7939 3983.4962)
      (12753.313 3988.687) (12748.1221 3992.1679) (12741.9847 3993.3893) (12735.8473 3992.1679) (12730.6565 3988.687)
      (12727.1756 3983.4962)
    ))
    ; P3660 -- see feature_dimensions_mm.csv
    ("06_ORNAMENT" 1 (
      (12725.9542 3901.0229) (12727.1756 3894.8855) (12730.6565 3889.6794) (12735.8473 3886.2137) (12741.9847 3884.9924)
      (12748.1221 3886.2137) (12753.313 3889.6794) (12756.7939 3894.8855) (12758.0153 3901.0229) (12756.7939 3907.1603)
      (12753.313 3912.3511) (12748.1221 3915.8321) (12741.9847 3917.0534) (12735.8473 3915.8321) (12730.6565 3912.3511)
      (12727.1756 3907.1603)
    ))
    ; P3661 -- see feature_dimensions_mm.csv
    ("06_ORNAMENT" 1 (
      (12742.5954 3007.6336) (12743.313 3006.3206) (12745.2366 3005.2519) (12747.8779 3004.5496) (12750.5191 3004.1985)
      (12752.5038 3003.9542) (12753.3893 3003.4962) (12753.084 3002.5649) (12751.8473 3000.9924) (12750.2443 2998.8702)
      (12748.8702 2996.5038) (12748.2443 2994.3817) (12748.6718 2992.9466) (12750.1069 2992.5191) (12752.229 2993.145)
      (12754.5954 2994.5191) (12756.7176 2996.1221) (12758.2901 2997.3588) (12759.2214 2997.6641) (12759.6794 2996.7786)
      (12759.9237 2994.7939) (12760.2748 2992.1527) (12760.9771 2989.5115) (12762.0458 2987.5878) (12763.3588 2986.8702)
      (12764.6718 2987.5878) (12765.7405 2989.5115) (12766.4427 2992.1527) (12766.7939 2994.7939) (12767.0382 2996.7786)
      (12767.4962 2997.6641) (12768.4275 2997.3588) (12770.0 2996.1221) (12772.1221 2994.5191) (12774.4885 2993.145)
      (12776.6107 2992.5191) (12778.0458 2992.9466) (12778.4733 2994.3817) (12777.8473 2996.5038) (12776.4733 2998.8702)
      (12774.8702 3000.9924) (12773.6336 3002.5649) (12773.3282 3003.4962) (12774.2137 3003.9542) (12776.1985 3004.1985)
      (12778.8397 3004.5496) (12781.4809 3005.2519) (12783.4046 3006.3206) (12784.1221 3007.6336) (12783.4046 3008.9466)
      (12781.4809 3010.0153) (12778.8397 3010.7176) (12776.1985 3011.0687) (12774.2137 3011.313) (12773.3282 3011.771)
      (12773.6336 3012.7023) (12774.8702 3014.2748) (12776.4733 3016.3969) (12777.8473 3018.7634) (12778.4733 3020.8855)
      (12778.0458 3022.3206) (12776.6107 3022.7481) (12774.4885 3022.1221) (12772.1221 3020.7481) (12770.0 3019.145)
      (12768.4275 3017.9084) (12767.4962 3017.6031) (12767.0382 3018.4885) (12766.7939 3020.4733) (12766.4427 3023.1145)
      (12765.7405 3025.7557) (12764.6718 3027.6794) (12763.3588 3028.3969) (12762.0458 3027.6794) (12760.9771 3025.7557)
      (12760.2748 3023.1145) (12759.9237 3020.4733) (12759.6794 3018.4885) (12759.2214 3017.6031) (12758.2901 3017.9084)
      (12756.7176 3019.145) (12754.5954 3020.7481) (12752.229 3022.1221) (12750.1069 3022.7481) (12748.6718 3022.3206)
      (12748.2443 3020.8855) (12748.8702 3018.7634) (12750.2443 3016.3969) (12751.8473 3014.2748) (12753.084 3012.7023)
      (12753.3893 3011.771) (12752.5038 3011.313) (12750.5191 3011.0687) (12747.8779 3010.7176) (12745.2366 3010.0153)
      (12743.313 3008.9466)
    ))
    ; P3662 -- see feature_dimensions_mm.csv
    ("06_ORNAMENT" 1 (
      (12742.5954 2900.7634) (12743.313 2899.4504) (12745.2366 2898.3817) (12747.8779 2897.6794) (12750.5191 2897.3282)
      (12752.5038 2897.084) (12753.3893 2896.626) (12753.084 2895.6947) (12751.8473 2894.1221) (12750.2443 2892.0)
      (12748.8702 2889.6336) (12748.2443 2887.5115) (12748.6718 2886.0763) (12750.1069 2885.6489) (12752.229 2886.2748)
      (12754.5954 2887.6489) (12756.7176 2889.2519) (12758.2901 2890.4885) (12759.2214 2890.7939) (12759.6794 2889.9084)
      (12759.9237 2887.9237) (12760.2748 2885.2824) (12760.9771 2882.6412) (12762.0458 2880.7176) (12763.3588 2880.0)
      (12764.6718 2880.7176) (12765.7405 2882.6412) (12766.4427 2885.2824) (12766.7939 2887.9237) (12767.0382 2889.9084)
      (12767.4962 2890.7939) (12768.4275 2890.4885) (12770.0 2889.2519) (12772.1221 2887.6489) (12774.4885 2886.2748)
      (12776.6107 2885.6489) (12778.0458 2886.0763) (12778.4733 2887.5115) (12777.8473 2889.6336) (12776.4733 2892.0)
      (12774.8702 2894.1221) (12773.6336 2895.6947) (12773.3282 2896.626) (12774.2137 2897.084) (12776.1985 2897.3282)
      (12778.8397 2897.6794) (12781.4809 2898.3817) (12783.4046 2899.4504) (12784.1221 2900.7634) (12783.4046 2902.0763)
      (12781.4809 2903.145) (12778.8397 2903.8473) (12776.1985 2904.1985) (12774.2137 2904.4427) (12773.3282 2904.9008)
      (12773.6336 2905.8321) (12774.8702 2907.4046) (12776.4733 2909.5267) (12777.8473 2911.8931) (12778.4733 2914.0153)
      (12778.0458 2915.4504) (12776.6107 2915.8779) (12774.4885 2915.2519) (12772.1221 2913.8779) (12770.0 2912.2748)
      (12768.4275 2911.0382) (12767.4962 2910.7328) (12767.0382 2911.6183) (12766.7939 2913.6031) (12766.4427 2916.2443)
      (12765.7405 2918.8855) (12764.6718 2920.8092) (12763.3588 2921.5267) (12762.0458 2920.8092) (12760.9771 2918.8855)
      (12760.2748 2916.2443) (12759.9237 2913.6031) (12759.6794 2911.6183) (12759.2214 2910.7328) (12758.2901 2911.0382)
      (12756.7176 2912.2748) (12754.5954 2913.8779) (12752.229 2915.2519) (12750.1069 2915.8779) (12748.6718 2915.4504)
      (12748.2443 2914.0153) (12748.8702 2911.8931) (12750.2443 2909.5267) (12751.8473 2907.4046) (12753.084 2905.8321)
      (12753.3893 2904.9008) (12752.5038 2904.4427) (12750.5191 2904.1985) (12747.8779 2903.8473) (12745.2366 2903.145)
      (12743.313 2902.0763)
    ))
    ; P3663 -- see feature_dimensions_mm.csv
    ("06_ORNAMENT" 1 (
      (12757.2519 3007.6336) (12757.7099 3005.2977) (12759.0382 3003.313) (12761.0229 3001.9847) (12763.3588 3001.5267)
      (12765.6947 3001.9847) (12767.6794 3003.313) (12769.0076 3005.2977) (12769.4656 3007.6336) (12769.0076 3009.9695)
      (12767.6794 3011.9542) (12765.6947 3013.2824) (12763.3588 3013.7405) (12761.0229 3013.2824) (12759.0382 3011.9542)
      (12757.7099 3009.9695)
    ))
    ; P3664 -- see feature_dimensions_mm.csv
    ("06_ORNAMENT" 1 (
      (12757.2519 2900.7634) (12757.7099 2898.4275) (12759.0382 2896.4427) (12761.0229 2895.1145) (12763.3588 2894.6565)
      (12765.6947 2895.1145) (12767.6794 2896.4427) (12769.0076 2898.4275) (12769.4656 2900.7634) (12769.0076 2903.0992)
      (12767.6794 2905.084) (12765.6947 2906.4122) (12763.3588 2906.8702) (12761.0229 2906.4122) (12759.0382 2905.084)
      (12757.7099 2903.0992)
    ))
    ; P3665 -- see feature_dimensions_mm.csv
    ("06_ORNAMENT" 1 (
      (12774.7328 1861.9237) (12776.7328 1848.2595) (12781.4046 1836.458) (12788.6565 1826.8244) (12798.2901 1819.5725)
      (12810.0916 1814.9008) (12823.7557 1812.9008) (12838.9313 1813.6489) (12855.2824 1817.1145) (12872.3664 1823.2061)
      (12889.8015 1831.771) (12907.1298 1842.626) (12923.9237 1855.4656) (12939.7863 1870.0) (12954.3206 1885.8626)
      (12967.1756 1902.6718) (12978.0153 1920.0) (12986.5954 1937.4198) (12992.687 1954.5191) (12996.1527 1970.855)
      (12996.8855 1986.0458) (12994.9008 1999.7099) (12990.229 2011.4962) (12982.9771 2021.145) (12973.3282 2028.3817)
      (12961.542 2033.0687) (12947.8779 2035.0534) (12932.687 2034.3053) (12916.3511 2030.855) (12899.2519 2024.7634)
      (12881.8321 2016.1832) (12864.5038 2005.3435) (12847.6947 1992.4885) (12831.8321 1977.9542) (12817.2977 1962.0916)
      (12804.458 1945.2977) (12793.6031 1927.9695) (12785.0382 1910.5344) (12778.9466 1893.4504) (12775.4809 1877.0992)
    ))
    ; P3666 -- see feature_dimensions_mm.csv
    ("06_ORNAMENT" 1 (
      (12774.7328 1618.9924) (12775.4809 1603.8168) (12778.9466 1587.4656) (12785.0382 1570.3817) (12793.6031 1552.9466)
      (12804.458 1535.6183) (12817.2977 1518.8244) (12831.8321 1502.9618) (12847.6947 1488.4275) (12864.5038 1475.5725)
      (12881.8321 1464.7328) (12899.2519 1456.1527) (12916.3511 1450.0611) (12932.687 1446.5954) (12947.8779 1445.8626)
      (12961.542 1447.8473) (12973.3282 1452.5191) (12982.9771 1459.771) (12990.229 1469.4198) (12994.9008 1481.2061)
      (12996.8855 1494.8702) (12996.1527 1510.0611) (12992.687 1526.3969) (12986.5954 1543.4962) (12978.0153 1560.916)
      (12967.1756 1578.2443) (12954.3206 1595.0534) (12939.7863 1610.916) (12923.9237 1625.4504) (12907.1298 1638.2901)
      (12889.8015 1649.145) (12872.3664 1657.7099) (12855.2824 1663.8015) (12838.9313 1667.2672) (12823.7557 1668.0153)
      (12810.0916 1666.0153) (12798.2901 1661.3435) (12788.6565 1654.0916) (12781.4046 1644.458) (12776.7328 1632.6565)
    ))
    ; P3667 -- see feature_dimensions_mm.csv
    ("06_ORNAMENT" 1 (
      (12778.626 5816.7939) (12806.3664 5815.4046) (12835.5573 5816.7481) (12865.8168 5820.5802) (12896.7634 5826.626)
      (12928.0153 5834.6565) (12959.1908 5844.3969) (12989.9237 5855.6183) (13019.8168 5868.0611) (13048.4885 5881.4656)
      (13075.5725 5895.5878) (13100.6718 5910.1832) (13123.4046 5924.9771) (13143.4198 5939.7405) (13160.3053 5954.1985)
      (13135.8473 5953.7863) (13109.2519 5951.7557) (13080.916 5948.1679) (13051.313 5943.0687) (13020.8397 5936.4733)
      (12989.9389 5928.4275) (12959.0229 5918.9771) (12928.5496 5908.1679) (12898.916 5896.0305) (12870.5802 5882.5954)
      (12843.9542 5867.9237) (12819.4656 5852.0305) (12797.542 5834.9771)
    ))
    ; P3668 -- see feature_dimensions_mm.csv
    ("06_ORNAMENT" 1 (
      (12802.9924 2099.7557) (12804.3359 2088.3664) (12807.1145 2077.9542) (12811.2672 2068.7786) (12816.7023 2061.0687)
      (12823.2824 2055.0076) (12830.8244 2050.7634) (12839.1603 2048.4275) (12848.0916 2048.0611) (12857.374 2049.6794)
      (12866.8092 2053.2214) (12876.1374 2058.6107) (12885.145 2065.7252) (12893.6183 2074.3817) (12901.3282 2084.3664)
      (12908.0916 2095.4351) (12913.7405 2107.313) (12918.1374 2119.7099) (12919.4046 2124.9618) (12923.1908 2124.2901)
      (12928.5344 2123.6031) (12932.3511 2122.8702) (12934.3359 2121.5267) (12934.5038 2119.145) (12933.2366 2115.4656)
      (12931.1603 2110.5038) (12929.0076 2104.5802) (12927.5267 2098.2901) (12927.2672 2092.3664) (12928.5191 2087.5573)
      (12931.2977 2084.5191) (12935.313 2083.6336) (12940.1069 2084.9466) (12945.1145 2088.1374) (12949.8168 2092.5802)
      (12953.8779 2097.3893) (12957.1298 2101.6641) (12959.6794 2104.6107) (12961.8321 2105.6489) (12963.9847 2104.6107)
      (12966.5344 2101.6641) (12969.7863 2097.3893) (12973.8473 2092.5802) (12978.5496 2088.1374) (12983.5573 2084.9466)
      (12988.3511 2083.6336) (12992.3664 2084.5191) (12995.145 2087.5573) (12996.3969 2092.3664) (12996.1374 2098.2901)
      (12994.6565 2104.5802) (12992.5038 2110.5038) (12990.4275 2115.4656) (12989.1603 2119.145) (12989.3282 2121.5267)
      (12991.313 2122.8702) (12995.1298 2123.6031) (13000.4733 2124.2901) (13006.6565 2125.3893) (13012.855 2127.2519)
      (13018.1221 2130.0) (13021.6641 2133.4809) (13022.9008 2137.4046) (13021.6641 2141.3282) (13018.1221 2144.8092)
      (13012.855 2147.5573) (13006.6565 2149.4198) (13000.4733 2150.5191) (12995.1298 2151.2061) (12991.313 2151.9389)
      (12989.3282 2153.2824) (12989.1603 2155.6641) (12990.4275 2159.3435) (12992.5038 2164.3053) (12994.6565 2170.229)
      (12995.6794 2174.5954) (12981.1145 2185.8473) (12979.2366 2187.0992) (12978.5496 2186.6718) (12973.8473 2182.229)
      (12969.7863 2177.4198) (12966.5344 2173.145) (12963.9847 2170.1985) (12961.8321 2169.1603) (12959.6794 2170.1985)
      (12957.1298 2173.145) (12953.8779 2177.4198) (12949.8168 2182.229) (12945.1145 2186.6718) (12940.1069 2189.8626)
      (12935.313 2191.1756) (12931.2977 2190.2901) (12928.5191 2187.2519) (12927.2672 2182.4427) (12927.5267 2176.5191)
      (12929.0076 2170.229) (12931.1603 2164.3053) (12933.2366 2159.3435) (12934.5038 2155.6641) (12934.3359 2153.2824)
      (12932.3511 2151.9389) (12928.5344 2151.2061) (12923.1908 2150.5191) (12922.855 2150.458) (12922.9313 2156.9313)
      (12921.5878 2168.3359) (12918.8092 2178.7481) (12914.6412 2187.9237) (12909.2061 2195.6336) (12902.6412 2201.6794)
      (12895.0992 2205.9237) (12886.7481 2208.2595) (12877.8321 2208.626) (12868.5344 2207.0229) (12859.1145 2203.4656)
      (12849.771 2198.0763) (12840.7634 2190.9618) (12832.3053 2182.3053) (12824.5954 2172.3206) (12817.8321 2161.2519)
      (12812.1832 2149.374) (12807.7863 2136.9771) (12804.7328 2124.3817) (12803.1298 2111.8626)
    ))
    ; P3669 -- see feature_dimensions_mm.csv
    ("06_ORNAMENT" 1 (
      (12802.9924 1381.145) (12803.1298 1369.0534) (12804.7328 1356.5344) (12807.7863 1343.9389) (12812.1832 1331.542)
      (12817.8321 1319.6641) (12824.5954 1308.5954) (12832.3053 1298.6107) (12840.7634 1289.9542) (12849.771 1282.8397)
      (12859.1145 1277.4504) (12868.5344 1273.8931) (12877.8321 1272.2901) (12886.7481 1272.6565) (12895.0992 1274.9924)
      (12902.6412 1279.2366) (12909.2061 1285.2824) (12914.6412 1292.9924) (12918.8092 1302.1679) (12921.5878 1312.5802)
      (12922.9313 1323.9847) (12922.7939 1336.0916) (12921.1756 1348.5954) (12918.1374 1361.2061) (12917.9084 1361.8779)
      (12923.1908 1360.9313) (12928.5344 1360.2443) (12932.3511 1359.5115) (12934.3359 1358.1679) (12934.5038 1355.7863)
      (12933.2366 1352.1069) (12931.1603 1347.145) (12929.0076 1341.2214) (12927.5267 1334.9313) (12927.2672 1329.0076)
      (12928.5191 1324.1985) (12931.2977 1321.1603) (12935.313 1320.2748) (12940.1069 1321.5878) (12945.1145 1324.7786)
      (12949.8168 1329.2214) (12953.8779 1334.0305) (12957.1298 1338.3053) (12959.6794 1341.2519) (12961.8321 1342.2901)
      (12963.9847 1341.2519) (12966.5344 1338.3053) (12969.7863 1334.0305) (12973.8473 1329.2214) (12978.5496 1324.7786)
      (12983.5573 1321.5878) (12988.3511 1320.2748) (12992.3664 1321.1603) (12995.145 1324.1985) (12996.3969 1329.0076)
      (12996.1374 1334.9313) (12994.6565 1341.2214) (12992.5038 1347.145) (12990.4275 1352.1069) (12989.1603 1355.7863)
      (12989.3282 1358.1679) (12991.313 1359.5115) (12995.1298 1360.2443) (13000.4733 1360.9313) (13006.6565 1362.0305)
      (13012.855 1363.8931) (13018.1221 1366.6412) (13021.6641 1370.1221) (13022.9008 1374.0458) (13021.6641 1377.9695)
      (13020.2443 1379.3588) (13026.1527 1378.4275) (13037.9542 1380.2901) (13048.5954 1385.7099) (13057.0382 1394.1527)
      (13062.458 1404.7939) (13064.3206 1416.5954) (13062.458 1428.3817) (13057.0382 1439.0229) (13048.5954 1447.4656)
      (13037.9542 1452.8855) (13026.1527 1454.7634) (13014.3664 1452.8855) (13003.7252 1447.4656) (12995.2824 1439.0229)
      (12989.8626 1428.3817) (12989.7252 1427.5115) (12988.3511 1427.8168) (12983.5573 1426.5038) (12978.5496 1423.313)
      (12973.8473 1418.8702) (12969.7863 1414.0611) (12966.5344 1409.7863) (12963.9847 1406.8397) (12961.8321 1405.8015)
      (12959.6794 1406.8397) (12957.1298 1409.7863) (12953.8779 1414.0611) (12949.8168 1418.8702) (12945.1145 1423.313)
      (12940.1069 1426.5038) (12935.313 1427.8168) (12931.2977 1426.9313) (12928.5191 1423.8931) (12927.2672 1419.084)
      (12927.5267 1413.1603) (12929.0076 1406.8702) (12931.1603 1400.9466) (12933.2366 1395.9847) (12934.5038 1392.3053)
      (12934.3359 1389.9237) (12932.3511 1388.5802) (12928.5344 1387.8473) (12923.1908 1387.1603) (12917.0076 1386.0611)
      (12910.8092 1384.1985) (12909.1145 1383.313) (12908.0916 1385.4809) (12901.3282 1396.5496) (12893.6183 1406.5344)
      (12885.145 1415.1908) (12876.1374 1422.3053) (12866.8092 1427.6947) (12857.374 1431.2366) (12848.0916 1432.855)
      (12839.1603 1432.4885) (12830.8244 1430.1527) (12823.2824 1425.9084) (12816.7023 1419.8473) (12811.2672 1412.1374)
      (12807.1145 1402.9618) (12804.3359 1392.5496)
    ))
    ; P3670 -- see feature_dimensions_mm.csv
    ("06_ORNAMENT" 1 (
      (12824.4275 1740.458) (12826.1221 1728.5191) (12831.145 1716.8702) (12839.4046 1705.8015) (12850.6718 1695.5878)
      (12864.6718 1686.4733) (12881.0687 1678.7023) (12899.4504 1672.4427) (12919.374 1667.8626) (12940.3359 1665.0687)
      (12961.8321 1664.1221) (12983.3282 1665.0687) (13004.2901 1667.8626) (13024.2137 1672.4427) (13042.5954 1678.7023)
      (13058.9924 1686.4733) (13072.9924 1695.5878) (13084.2595 1705.8015) (13092.5191 1716.8702) (13097.542 1728.5191)
      (13099.2366 1740.458) (13097.542 1752.3969) (13092.5191 1764.0458) (13084.2595 1775.1145) (13072.9924 1785.3282)
      (13058.9924 1794.4427) (13042.5954 1802.2137) (13024.2137 1808.4733) (13004.2901 1813.0534) (12983.3282 1815.8473)
      (12961.8321 1816.7939) (12940.3359 1815.8473) (12919.374 1813.0534) (12899.4504 1808.4733) (12881.0687 1802.2137)
      (12864.6718 1794.4427) (12850.6718 1785.3282) (12839.4046 1775.1145) (12831.145 1764.0458) (12826.1221 1752.3969)
    ))
    ; P3671 -- see feature_dimensions_mm.csv
    ("06_ORNAMENT" 1 (
      (12987.9847 2064.3206) (12989.8626 2052.5344) (12995.2824 2041.8931) (13003.7252 2033.4504) (13014.3664 2028.0305)
      (13026.1527 2026.1527) (13037.9542 2028.0305) (13048.5954 2033.4504) (13057.0382 2041.8931) (13062.458 2052.5344)
      (13064.3206 2064.3206) (13062.458 2076.1221) (13057.0382 2086.7634) (13048.5954 2095.2061) (13037.9542 2100.626)
      (13026.1527 2102.4885) (13014.3664 2100.626) (13003.7252 2095.2061) (12995.2824 2086.7634) (12989.8626 2076.1221)
    ))
    ; P3672 -- see feature_dimensions_mm.csv
    ("06_ORNAMENT" 1 (
      (12989.1603 1392.3053) (12990.4275 1395.9847) (12992.1985 1400.1985) (12995.2824 1394.1527) (13002.6718 1386.7634)
      (13000.4733 1387.1603) (12995.1298 1387.8473) (12991.313 1388.5802) (12989.3282 1389.9237)
    ))
    ; P3673 -- see feature_dimensions_mm.csv
    ("06_ORNAMENT" 1 (
      (13009.8931 1886.2595) (13010.2595 1877.3282) (13012.5954 1868.9924) (13016.8397 1861.4504) (13022.9008 1854.8702)
      (13030.6107 1849.4351) (13039.7863 1845.2824) (13050.1985 1842.5038) (13061.6031 1841.1603) (13073.6947 1841.2977)
      (13086.2137 1842.9008) (13098.8092 1845.9542) (13111.2061 1850.3511) (13123.084 1856.0) (13134.1527 1862.7634)
      (13144.1374 1870.4733) (13152.7939 1878.9313) (13157.9542 1885.4809) (13156.3817 1900.4733) (13151.5115 1928.2748)
      (13144.8702 1955.0229) (13140.5802 1956.9771) (13130.1679 1959.7557) (13118.7634 1961.0992) (13106.6565 1960.9618)
      (13094.1527 1959.3435) (13081.542 1956.3053) (13069.145 1951.9084) (13057.2672 1946.2595) (13046.1985 1939.4962)
      (13036.2137 1931.7863) (13027.5573 1923.313) (13020.4427 1914.3053) (13015.0534 1904.9771) (13011.5115 1895.542)
    ))
    ; P3674 -- see feature_dimensions_mm.csv
    ("06_ORNAMENT" 1 (
      (13013.7405 7374.0458) (13015.0992 7371.5267) (13018.8092 7369.4809) (13023.8473 7368.1527) (13028.9008 7367.4656)
      (13032.687 7367.0076) (13034.3664 7366.1527) (13033.771 7364.3511) (13031.4351 7361.3435) (13028.3511 7357.2824)
      (13025.7252 7352.7786) (13024.5496 7348.7176) (13025.374 7345.9847) (13028.1069 7345.1603) (13032.1679 7346.3359)
      (13036.6718 7348.9618) (13040.7328 7352.0458) (13043.7405 7354.3817) (13045.542 7354.9771) (13046.3969 7353.2977)
      (13046.855 7349.5115) (13047.5573 7344.458) (13048.8702 7339.4198) (13050.916 7335.7099) (13053.4351 7334.3511)
      (13055.9542 7335.7099) (13058.0 7339.4198) (13059.3282 7344.458) (13060.0153 7349.5115) (13060.4733 7353.2977)
      (13061.3282 7354.9771) (13063.1298 7354.3817) (13066.1374 7352.0458) (13070.1985 7348.9618) (13074.7023 7346.3359)
      (13078.7634 7345.1603) (13081.4962 7345.9847) (13082.3206 7348.7176) (13081.145 7352.7786) (13078.5191 7357.2824)
      (13075.4351 7361.3435) (13073.0992 7364.3511) (13072.5038 7366.1527) (13074.1832 7367.0076) (13077.9695 7367.4656)
      (13083.0229 7368.1527) (13088.0611 7369.4809) (13091.771 7371.5267) (13093.1298 7374.0458) (13091.771 7376.5649)
      (13088.0611 7378.6107) (13083.0229 7379.9237) (13077.9695 7380.626) (13074.1832 7381.084) (13072.5038 7381.9389)
      (13073.0992 7383.7405) (13075.4351 7386.7481) (13078.5191 7390.8092) (13081.145 7395.313) (13082.3206 7399.374)
      (13081.4962 7402.1069) (13078.7634 7402.9313) (13074.7023 7401.7557) (13070.1985 7399.1298) (13066.1374 7396.0458)
      (13063.1298 7393.7099) (13061.3282 7393.1145) (13060.4733 7394.7939) (13060.0153 7398.5802) (13059.3282 7403.6336)
      (13058.0 7408.6718) (13055.9542 7412.3817) (13053.4351 7413.7405) (13050.916 7412.3817) (13048.8702 7408.6718)
      (13047.5573 7403.6336) (13046.855 7398.5802) (13046.3969 7394.7939) (13045.542 7393.1145) (13043.7405 7393.7099)
      (13040.7328 7396.0458) (13036.6718 7399.1298) (13032.1679 7401.7557) (13028.1069 7402.9313) (13025.374 7402.1069)
      (13024.5496 7399.374) (13025.7252 7395.313) (13028.3511 7390.8092) (13031.4351 7386.7481) (13033.771 7383.7405)
      (13034.3664 7381.9389) (13032.687 7381.084) (13028.9008 7380.626) (13023.8473 7379.9237) (13018.8092 7378.6107)
      (13015.0992 7376.5649)
    ))
    ; P3675 -- see feature_dimensions_mm.csv
    ("06_ORNAMENT" 1 (
      (13013.7405 7206.1069) (13015.0992 7203.5878) (13018.8092 7201.542) (13023.8473 7200.2137) (13028.9008 7199.5267)
      (13032.687 7199.0687) (13034.3664 7198.2137) (13033.771 7196.4122) (13031.4351 7193.4046) (13028.3511 7189.3435)
      (13025.7252 7184.8397) (13024.5496 7180.7786) (13025.374 7178.0458) (13028.1069 7177.2214) (13032.1679 7178.3969)
      (13036.6718 7181.0229) (13040.7328 7184.1069) (13043.7405 7186.4427) (13045.542 7187.0382) (13046.3969 7185.3588)
      (13046.855 7181.5725) (13047.5573 7176.5191) (13048.8702 7171.4809) (13050.916 7167.771) (13053.4351 7166.4122)
      (13055.9542 7167.771) (13058.0 7171.4809) (13059.3282 7176.5191) (13060.0153 7181.5725) (13060.4733 7185.3588)
      (13061.3282 7187.0382) (13063.1298 7186.4427) (13066.1374 7184.1069) (13070.1985 7181.0229) (13074.7023 7178.3969)
      (13078.7634 7177.2214) (13081.4962 7178.0458) (13082.3206 7180.7786) (13081.145 7184.8397) (13078.5191 7189.3435)
      (13075.4351 7193.4046) (13073.0992 7196.4122) (13072.5038 7198.2137) (13074.1832 7199.0687) (13077.9695 7199.5267)
      (13083.0229 7200.2137) (13088.0611 7201.542) (13091.771 7203.5878) (13093.1298 7206.1069) (13091.771 7208.626)
      (13088.0611 7210.6718) (13083.0229 7211.9847) (13077.9695 7212.687) (13074.1832 7213.145) (13072.5038 7214.0)
      (13073.0992 7215.8015) (13075.4351 7218.8092) (13078.5191 7222.8702) (13081.145 7227.374) (13082.3206 7231.4351)
      (13081.4962 7234.1679) (13078.7634 7234.9924) (13074.7023 7233.8168) (13070.1985 7231.1908) (13066.1374 7228.1069)
      (13063.1298 7225.771) (13061.3282 7225.1756) (13060.4733 7226.855) (13060.0153 7230.6412) (13059.3282 7235.6947)
      (13058.0 7240.7328) (13055.9542 7244.4427) (13053.4351 7245.8015) (13050.916 7244.4427) (13048.8702 7240.7328)
      (13047.5573 7235.6947) (13046.855 7230.6412) (13046.3969 7226.855) (13045.542 7225.1756) (13043.7405 7225.771)
      (13040.7328 7228.1069) (13036.6718 7231.1908) (13032.1679 7233.8168) (13028.1069 7234.9924) (13025.374 7234.1679)
      (13024.5496 7231.4351) (13025.7252 7227.374) (13028.3511 7222.8702) (13031.4351 7218.8092) (13033.771 7215.8015)
      (13034.3664 7214.0) (13032.687 7213.145) (13028.9008 7212.687) (13023.8473 7211.9847) (13018.8092 7210.6718)
      (13015.0992 7208.626)
    ))
    ; P3676 -- see feature_dimensions_mm.csv
    ("06_ORNAMENT" 1 (
      (13032.6718 3007.6336) (13033.3893 3006.3206) (13035.313 3005.2519) (13037.9542 3004.5496) (13040.5954 3004.1985)
      (13042.5802 3003.9542) (13043.4656 3003.4962) (13043.1603 3002.5649) (13041.9237 3000.9924) (13040.3206 2998.8702)
      (13038.9466 2996.5038) (13038.3206 2994.3817) (13038.7481 2992.9466) (13040.1832 2992.5191) (13042.3053 2993.145)
      (13044.6718 2994.5191) (13046.7939 2996.1221) (13048.3664 2997.3588) (13049.2977 2997.6641) (13049.7557 2996.7786)
      (13050.0 2994.7939) (13050.3511 2992.1527) (13051.0534 2989.5115) (13052.1221 2987.5878) (13053.4351 2986.8702)
      (13054.7481 2987.5878) (13055.8168 2989.5115) (13056.5191 2992.1527) (13056.8702 2994.7939) (13057.1145 2996.7786)
      (13057.5725 2997.6641) (13058.5038 2997.3588) (13060.0763 2996.1221) (13062.1985 2994.5191) (13064.5649 2993.145)
      (13066.687 2992.5191) (13068.1221 2992.9466) (13068.5496 2994.3817) (13067.9237 2996.5038) (13066.5496 2998.8702)
      (13064.9466 3000.9924) (13063.7099 3002.5649) (13063.4046 3003.4962) (13064.2901 3003.9542) (13066.2748 3004.1985)
      (13068.916 3004.5496) (13071.5573 3005.2519) (13073.4809 3006.3206) (13074.1985 3007.6336) (13073.4809 3008.9466)
      (13071.5573 3010.0153) (13068.916 3010.7176) (13066.2748 3011.0687) (13064.2901 3011.313) (13063.4046 3011.771)
      (13063.7099 3012.7023) (13064.9466 3014.2748) (13066.5496 3016.3969) (13067.9237 3018.7634) (13068.5496 3020.8855)
      (13068.1221 3022.3206) (13066.687 3022.7481) (13064.5649 3022.1221) (13062.1985 3020.7481) (13060.0763 3019.145)
      (13058.5038 3017.9084) (13057.5725 3017.6031) (13057.1145 3018.4885) (13056.8702 3020.4733) (13056.5191 3023.1145)
      (13055.8168 3025.7557) (13054.7481 3027.6794) (13053.4351 3028.3969) (13052.1221 3027.6794) (13051.0534 3025.7557)
      (13050.3511 3023.1145) (13050.0 3020.4733) (13049.7557 3018.4885) (13049.2977 3017.6031) (13048.3664 3017.9084)
      (13046.7939 3019.145) (13044.6718 3020.7481) (13042.3053 3022.1221) (13040.1832 3022.7481) (13038.7481 3022.3206)
      (13038.3206 3020.8855) (13038.9466 3018.7634) (13040.3206 3016.3969) (13041.9237 3014.2748) (13043.1603 3012.7023)
      (13043.4656 3011.771) (13042.5802 3011.313) (13040.5954 3011.0687) (13037.9542 3010.7176) (13035.313 3010.0153)
      (13033.3893 3008.9466)
    ))
    ; P3677 -- see feature_dimensions_mm.csv
    ("06_ORNAMENT" 1 (
      (13032.6718 2900.7634) (13033.3893 2899.4504) (13035.313 2898.3817) (13037.9542 2897.6794) (13040.5954 2897.3282)
      (13042.5802 2897.084) (13043.4656 2896.626) (13043.1603 2895.6947) (13041.9237 2894.1221) (13040.3206 2892.0)
      (13038.9466 2889.6336) (13038.3206 2887.5115) (13038.7481 2886.0763) (13040.1832 2885.6489) (13042.3053 2886.2748)
      (13044.6718 2887.6489) (13046.7939 2889.2519) (13048.3664 2890.4885) (13049.2977 2890.7939) (13049.7557 2889.9084)
      (13050.0 2887.9237) (13050.3511 2885.2824) (13051.0534 2882.6412) (13052.1221 2880.7176) (13053.4351 2880.0)
      (13054.7481 2880.7176) (13055.8168 2882.6412) (13056.5191 2885.2824) (13056.8702 2887.9237) (13057.1145 2889.9084)
      (13057.5725 2890.7939) (13058.5038 2890.4885) (13060.0763 2889.2519) (13062.1985 2887.6489) (13064.5649 2886.2748)
      (13066.687 2885.6489) (13068.1221 2886.0763) (13068.5496 2887.5115) (13067.9237 2889.6336) (13066.5496 2892.0)
      (13064.9466 2894.1221) (13063.7099 2895.6947) (13063.4046 2896.626) (13064.2901 2897.084) (13066.2748 2897.3282)
      (13068.916 2897.6794) (13071.5573 2898.3817) (13073.4809 2899.4504) (13074.1985 2900.7634) (13073.4809 2902.0763)
      (13071.5573 2903.145) (13068.916 2903.8473) (13066.2748 2904.1985) (13064.2901 2904.4427) (13063.4046 2904.9008)
      (13063.7099 2905.8321) (13064.9466 2907.4046) (13066.5496 2909.5267) (13067.9237 2911.8931) (13068.5496 2914.0153)
      (13068.1221 2915.4504) (13066.687 2915.8779) (13064.5649 2915.2519) (13062.1985 2913.8779) (13060.0763 2912.2748)
      (13058.5038 2911.0382) (13057.5725 2910.7328) (13057.1145 2911.6183) (13056.8702 2913.6031) (13056.5191 2916.2443)
      (13055.8168 2918.8855) (13054.7481 2920.8092) (13053.4351 2921.5267) (13052.1221 2920.8092) (13051.0534 2918.8855)
      (13050.3511 2916.2443) (13050.0 2913.6031) (13049.7557 2911.6183) (13049.2977 2910.7328) (13048.3664 2911.0382)
      (13046.7939 2912.2748) (13044.6718 2913.8779) (13042.3053 2915.2519) (13040.1832 2915.8779) (13038.7481 2915.4504)
      (13038.3206 2914.0153) (13038.9466 2911.8931) (13040.3206 2909.5267) (13041.9237 2907.4046) (13043.1603 2905.8321)
      (13043.4656 2904.9008) (13042.5802 2904.4427) (13040.5954 2904.1985) (13037.9542 2903.8473) (13035.313 2903.145)
      (13033.3893 2902.0763)
    ))
    ; P3678 -- see feature_dimensions_mm.csv
    ("06_ORNAMENT" 1 (
      (13044.3053 7374.0458) (13045.0076 7370.5496) (13046.9771 7367.5878) (13049.9389 7365.6183) (13053.4351 7364.916)
      (13056.9313 7365.6183) (13059.8931 7367.5878) (13061.8626 7370.5496) (13062.5649 7374.0458) (13061.8626 7377.542)
      (13059.8931 7380.5038) (13056.9313 7382.4733) (13053.4351 7383.1756) (13049.9389 7382.4733) (13046.9771 7380.5038)
      (13045.0076 7377.542)
    ))
    ; P3679 -- see feature_dimensions_mm.csv
    ("06_ORNAMENT" 1 (
      (13044.3053 7206.1069) (13045.0076 7202.6107) (13046.9771 7199.6489) (13049.9389 7197.6794) (13053.4351 7196.9771)
      (13056.9313 7197.6794) (13059.8931 7199.6489) (13061.8626 7202.6107) (13062.5649 7206.1069) (13061.8626 7209.6031)
      (13059.8931 7212.5649) (13056.9313 7214.5344) (13053.4351 7215.2366) (13049.9389 7214.5344) (13046.9771 7212.5649)
      (13045.0076 7209.6031)
    ))
    ; P3680 -- see feature_dimensions_mm.csv
    ("06_ORNAMENT" 1 (
      (13047.3282 3007.6336) (13047.7863 3005.2977) (13049.1145 3003.313) (13051.0992 3001.9847) (13053.4351 3001.5267)
      (13055.771 3001.9847) (13057.7557 3003.313) (13059.084 3005.2977) (13059.542 3007.6336) (13059.084 3009.9695)
      (13057.7557 3011.9542) (13055.771 3013.2824) (13053.4351 3013.7405) (13051.0992 3013.2824) (13049.1145 3011.9542)
      (13047.7863 3009.9695)
    ))
    ; P3681 -- see feature_dimensions_mm.csv
    ("06_ORNAMENT" 1 (
      (13047.3282 2900.7634) (13047.7863 2898.4275) (13049.1145 2896.4427) (13051.0992 2895.1145) (13053.4351 2894.6565)
      (13055.771 2895.1145) (13057.7557 2896.4427) (13059.084 2898.4275) (13059.542 2900.7634) (13059.084 2903.0992)
      (13057.7557 2905.084) (13055.771 2906.4122) (13053.4351 2906.8702) (13051.0992 2906.4122) (13049.1145 2905.084)
      (13047.7863 2903.0992)
    ))
    ; P3682 -- see feature_dimensions_mm.csv
    ("06_ORNAMENT" 1 (
      (13099.2366 5603.0534) (13125.4351 5607.6489) (13152.2748 5615.1908) (13179.4962 5625.3435) (13182.7481 5626.8244)
      (13183.9389 5620.8092) (13190.8397 5606.1069) (13202.8855 5596.229) (13220.5038 5589.8779) (13241.6489 5586.5038)
      (13264.2443 5585.4962) (13286.2443 5586.3053) (13305.6183 5588.3511) (13320.3053 5591.084) (13328.2443 5593.8931)
      (13328.626 5597.3435) (13323.0382 5602.1985) (13313.0687 5608.2443) (13300.3053 5615.2672) (13286.3359 5623.0534)
      (13272.7634 5631.3893) (13261.1603 5640.0611) (13253.1298 5648.855) (13247.9695 5658.1985) (13247.1756 5660.229)
      (13260.4275 5668.2137) (13286.1985 5685.5725) (13309.9084 5703.2214) (13311.6336 5702.9313) (13317.8931 5703.6031)
      (13324.7328 5705.6641) (13331.8015 5708.9618) (13338.7634 5713.3435) (13345.2977 5718.626) (13351.0534 5724.6718)
      (13355.7252 5731.2977) (13359.7252 5739.0382) (13363.5573 5748.2595) (13364.3969 5750.7939) (13375.4809 5761.7252)
      (13392.916 5780.8092) (13407.7863 5799.2824) (13419.8473 5816.7939) (13397.1756 5811.1603) (13372.9008 5803.5267)
      (13372.3053 5803.2977) (13372.2901 5803.4962) (13370.3817 5813.7405) (13366.6565 5823.8015) (13361.2214 5834.2748)
      (13354.4122 5844.8397) (13346.5649 5855.145) (13338.0305 5864.8702) (13329.1603 5873.6336) (13320.2901 5881.145)
      (13311.7557 5887.0229) (13303.1145 5891.7863) (13293.8626 5895.9847) (13284.2137 5899.3282) (13274.4275 5901.5267)
      (13264.7176 5902.2901) (13255.3282 5901.3282) (13246.5038 5898.3817) (13238.4733 5893.1298) (13230.9618 5885.4046)
      (13223.6489 5875.374) (13216.6412 5863.3588) (13210.0763 5849.6183) (13204.0916 5834.4427) (13198.7939 5818.1221)
      (13194.3359 5800.9466) (13190.8397 5783.2061) (13187.6183 5763.1603) (13184.2748 5739.7863) (13181.313 5714.4733)
      (13179.8321 5695.6031) (13168.1679 5685.9847) (13147.084 5666.1832) (13128.3206 5645.6641) (13112.2443 5624.5802)
    ))
    ; P3683 -- see feature_dimensions_mm.csv
    ("06_ORNAMENT" 1 (
      (13209.4809 4091.5573) (13209.9237 4101.0687) (13211.2672 4110.3359) (13213.7557 4119.8168) (13217.1756 4129.2061)
      (13221.374 4138.229) (13226.1374 4146.6107) (13231.2824 4154.0305) (13236.626 4160.2137) (13241.9847 4164.8855)
      (13248.1679 4167.9542) (13255.6947 4169.6641) (13263.9542 4170.2137) (13272.3359 4169.7863) (13280.1985 4168.5496)
      (13286.9618 4166.7176) (13291.9847 4164.4733) (13294.6565 4161.9847) (13294.2443 4159.0382) (13291.0382 4155.3435)
      (13285.9237 4151.0229) (13279.771 4146.2137) (13273.4809 4141.0076) (13267.9237 4135.542) (13264.0 4129.9237)
      (13262.5954 4124.2748) (13263.5267 4117.9084) (13265.8626 4110.4122) (13269.4046 4102.3206) (13273.9084 4094.1832)
      (13279.1298 4086.5496) (13284.8702 4079.9542) (13290.8855 4074.9466) (13295.313 4072.8397) (13291.8473 4058.1374)
      (13288.9618 4040.0) (13288.1221 4022.3969) (13289.4046 4011.8321) (13284.0763 4002.7786) (13278.6107 3992.5496)
      (13272.0458 3995.3435) (13255.084 4003.2519) (13240.5802 4011.4962) (13230.5344 4019.8473) (13224.0916 4028.7328)
      (13218.9924 4038.5191) (13215.1298 4048.9466) (13212.3511 4059.7252) (13210.5802 4070.6107) (13209.6489 4081.313)
    ))
    ; P3684 -- see feature_dimensions_mm.csv
    ("06_ORNAMENT" 1 (
      (13233.313 3960.0305) (13244.4122 3959.6489) (13261.9084 3960.1527) (13258.6565 3953.2519) (13249.0076 3956.4885)
      (13238.5649 3959.1603)
    ))
    ; P3685 -- see feature_dimensions_mm.csv
    ("06_ORNAMENT" 1 (
      (13236.9313 5736.9924) (13237.7252 5744.1069) (13239.7099 5754.0763) (13242.4427 5763.9695) (13245.8015 5773.4656)
      (13249.6183 5782.2901) (13253.7252 5790.1069) (13258.0 5796.6107) (13262.2901 5801.5267) (13267.2366 5804.7634)
      (13273.2519 5806.5649) (13279.8626 5807.1298) (13286.5649 5806.6718) (13292.8702 5805.3893) (13298.2748 5803.4656)
      (13302.2901 5801.084) (13304.4275 5798.4733) (13304.1069 5795.374) (13301.542 5791.4809) (13297.4351 5786.9466)
      (13292.5191 5781.8626) (13287.4809 5776.3969) (13283.0382 5770.6412) (13279.9084 5764.7176) (13279.3588 5761.8168)
      (13267.6947 5755.5725) (13241.313 5739.8779)
    ))
    ; P3686 -- see feature_dimensions_mm.csv
    ("06_ORNAMENT" 1 (
      (13264.5496 3950.8855) (13274.8702 3960.6718) (13286.687 3961.6183) (13278.5191 3947.6641) (13277.0687 3944.9008)
      (13268.3969 3949.313)
    ))
    ; P3687 -- see feature_dimensions_mm.csv
    ("06_ORNAMENT" 1 (
      (13331.6183 5206.0611) (13332.0611 5215.5725) (13333.4046 5224.8397) (13335.8931 5234.3206) (13339.313 5243.7099)
      (13343.5115 5252.7328) (13348.2748 5261.1145) (13353.4198 5268.5344) (13358.7634 5274.7176) (13364.1221 5279.3893)
      (13370.3053 5282.458) (13377.8321 5284.1679) (13386.0916 5284.7176) (13394.4733 5284.2901) (13402.3359 5283.0534)
      (13409.0992 5281.2214) (13414.1221 5278.9771) (13416.7939 5276.4885) (13416.3817 5273.542) (13413.1756 5269.8473)
      (13408.0611 5265.5267) (13401.9084 5260.7176) (13395.6183 5255.5115) (13390.0611 5250.0458) (13386.1374 5244.4275)
      (13384.7328 5238.7786) (13385.6641 5232.4122) (13388.0 5224.916) (13391.542 5216.8244) (13396.0458 5208.687)
      (13401.2672 5201.0534) (13407.0076 5194.458) (13413.0229 5189.4504) (13419.084 5186.5649) (13425.8015 5185.7252)
      (13429.5725 5186.0305) (13413.1756 5172.3206) (13372.5496 5136.3511) (13362.0611 5126.5344) (13352.6718 5134.3511)
      (13346.229 5143.2366) (13341.1298 5153.0229) (13337.2672 5163.4504) (13334.4885 5174.229) (13332.7176 5185.1145)
      (13331.7863 5195.8168)
    ))
    ; P3688 -- see feature_dimensions_mm.csv
    ("06_ORNAMENT" 1 (
      (13358.7023 4204.1985) (13366.5496 4203.9237) (13394.0611 4204.7023) (13418.2748 4206.6565) (13423.0076 4207.313)
      (13409.4198 4189.5878) (13396.7176 4188.9466) (13384.1985 4186.8855) (13373.6947 4183.4809) (13372.4427 4186.0458)
      (13365.6489 4196.0)
    ))
    ; P3689 -- see feature_dimensions_mm.csv
    ("06_ORNAMENT" 1 (
      (13487.0229 7374.0458) (13488.3817 7371.5267) (13492.0916 7369.4809) (13497.1298 7368.1527) (13502.1832 7367.4656)
      (13505.9695 7367.0076) (13507.6489 7366.1527) (13507.0534 7364.3511) (13504.7176 7361.3435) (13501.6336 7357.2824)
      (13499.0076 7352.7786) (13497.8321 7348.7176) (13498.6565 7345.9847) (13501.3893 7345.1603) (13505.4504 7346.3359)
      (13509.9542 7348.9618) (13514.0153 7352.0458) (13517.0229 7354.3817) (13518.8244 7354.9771) (13519.6794 7353.2977)
      (13520.1374 7349.5115) (13520.8397 7344.458) (13522.1527 7339.4198) (13524.1985 7335.7099) (13526.7176 7334.3511)
      (13529.2366 7335.7099) (13531.2824 7339.4198) (13532.6107 7344.458) (13533.2977 7349.5115) (13533.7557 7353.2977)
      (13534.6107 7354.9771) (13536.4122 7354.3817) (13539.4198 7352.0458) (13543.4809 7348.9618) (13547.9847 7346.3359)
      (13552.0458 7345.1603) (13554.7786 7345.9847) (13555.6031 7348.7176) (13554.4275 7352.7786) (13551.8015 7357.2824)
      (13548.7176 7361.3435) (13546.3817 7364.3511) (13545.7863 7366.1527) (13547.4656 7367.0076) (13551.2519 7367.4656)
      (13556.3053 7368.1527) (13561.3435 7369.4809) (13565.0534 7371.5267) (13566.4122 7374.0458) (13565.0534 7376.5649)
      (13561.3435 7378.6107) (13556.3053 7379.9237) (13551.2519 7380.626) (13547.4656 7381.084) (13545.7863 7381.9389)
      (13546.3817 7383.7405) (13548.7176 7386.7481) (13551.8015 7390.8092) (13554.4275 7395.313) (13555.6031 7399.374)
      (13554.7786 7402.1069) (13552.0458 7402.9313) (13547.9847 7401.7557) (13543.4809 7399.1298) (13539.4198 7396.0458)
      (13536.4122 7393.7099) (13534.6107 7393.1145) (13533.7557 7394.7939) (13533.2977 7398.5802) (13532.6107 7403.6336)
      (13531.2824 7408.6718) (13529.2366 7412.3817) (13526.7176 7413.7405) (13524.1985 7412.3817) (13522.1527 7408.6718)
      (13520.8397 7403.6336) (13520.1374 7398.5802) (13519.6794 7394.7939) (13518.8244 7393.1145) (13517.0229 7393.7099)
      (13514.0153 7396.0458) (13509.9542 7399.1298) (13505.4504 7401.7557) (13501.3893 7402.9313) (13498.6565 7402.1069)
      (13497.8321 7399.374) (13499.0076 7395.313) (13501.6336 7390.8092) (13504.7176 7386.7481) (13507.0534 7383.7405)
      (13507.6489 7381.9389) (13505.9695 7381.084) (13502.1832 7380.626) (13497.1298 7379.9237) (13492.0916 7378.6107)
      (13488.3817 7376.5649)
    ))
    ; P3690 -- see feature_dimensions_mm.csv
    ("06_ORNAMENT" 1 (
      (13487.0229 7206.1069) (13488.3817 7203.5878) (13492.0916 7201.542) (13497.1298 7200.2137) (13502.1832 7199.5267)
      (13505.9695 7199.0687) (13507.6489 7198.2137) (13507.0534 7196.4122) (13504.7176 7193.4046) (13501.6336 7189.3435)
      (13499.0076 7184.8397) (13497.8321 7180.7786) (13498.6565 7178.0458) (13501.3893 7177.2214) (13505.4504 7178.3969)
      (13509.9542 7181.0229) (13514.0153 7184.1069) (13517.0229 7186.4427) (13518.8244 7187.0382) (13519.6794 7185.3588)
      (13520.1374 7181.5725) (13520.8397 7176.5191) (13522.1527 7171.4809) (13524.1985 7167.771) (13526.7176 7166.4122)
      (13529.2366 7167.771) (13531.2824 7171.4809) (13532.6107 7176.5191) (13533.2977 7181.5725) (13533.7557 7185.3588)
      (13534.6107 7187.0382) (13536.4122 7186.4427) (13539.4198 7184.1069) (13543.4809 7181.0229) (13547.9847 7178.3969)
      (13552.0458 7177.2214) (13554.7786 7178.0458) (13555.6031 7180.7786) (13554.4275 7184.8397) (13551.8015 7189.3435)
      (13548.7176 7193.4046) (13546.3817 7196.4122) (13545.7863 7198.2137) (13547.4656 7199.0687) (13551.2519 7199.5267)
      (13556.3053 7200.2137) (13561.3435 7201.542) (13565.0534 7203.5878) (13566.4122 7206.1069) (13565.0534 7208.626)
      (13561.3435 7210.6718) (13556.3053 7211.9847) (13551.2519 7212.687) (13547.4656 7213.145) (13545.7863 7214.0)
      (13546.3817 7215.8015) (13548.7176 7218.8092) (13551.8015 7222.8702) (13554.4275 7227.374) (13555.6031 7231.4351)
      (13554.7786 7234.1679) (13552.0458 7234.9924) (13547.9847 7233.8168) (13543.4809 7231.1908) (13539.4198 7228.1069)
      (13536.4122 7225.771) (13534.6107 7225.1756) (13533.7557 7226.855) (13533.2977 7230.6412) (13532.6107 7235.6947)
      (13531.2824 7240.7328) (13529.2366 7244.4427) (13526.7176 7245.8015) (13524.1985 7244.4427) (13522.1527 7240.7328)
      (13520.8397 7235.6947) (13520.1374 7230.6412) (13519.6794 7226.855) (13518.8244 7225.1756) (13517.0229 7225.771)
      (13514.0153 7228.1069) (13509.9542 7231.1908) (13505.4504 7233.8168) (13501.3893 7234.9924) (13498.6565 7234.1679)
      (13497.8321 7231.4351) (13499.0076 7227.374) (13501.6336 7222.8702) (13504.7176 7218.8092) (13507.0534 7215.8015)
      (13507.6489 7214.0) (13505.9695 7213.145) (13502.1832 7212.687) (13497.1298 7211.9847) (13492.0916 7210.6718)
      (13488.3817 7208.626)
    ))
    ; P3691 -- see feature_dimensions_mm.csv
    ("06_ORNAMENT" 1 (
      (13517.5878 7374.0458) (13518.2901 7370.5496) (13520.2595 7367.5878) (13523.2214 7365.6183) (13526.7176 7364.916)
      (13530.2137 7365.6183) (13533.1756 7367.5878) (13535.145 7370.5496) (13535.8473 7374.0458) (13535.145 7377.542)
      (13533.1756 7380.5038) (13530.2137 7382.4733) (13526.7176 7383.1756) (13523.2214 7382.4733) (13520.2595 7380.5038)
      (13518.2901 7377.542)
    ))
    ; P3692 -- see feature_dimensions_mm.csv
    ("06_ORNAMENT" 1 (
      (13517.5878 7206.1069) (13518.2901 7202.6107) (13520.2595 7199.6489) (13523.2214 7197.6794) (13526.7176 7196.9771)
      (13530.2137 7197.6794) (13533.1756 7199.6489) (13535.145 7202.6107) (13535.8473 7206.1069) (13535.145 7209.6031)
      (13533.1756 7212.5649) (13530.2137 7214.5344) (13526.7176 7215.2366) (13523.2214 7214.5344) (13520.2595 7212.5649)
      (13518.2901 7209.6031)
    ))
    ; P3693 -- see feature_dimensions_mm.csv
    ("07_RAILINGS" 0 (
      (1038.1679 5816.7939) (1058.0153 5816.7939)
    ))
    ; P3694 -- see feature_dimensions_mm.csv
    ("07_RAILINGS" 0 (
      (1038.1679 5465.6489) (1038.1679 5816.7939)
    ))
    ; P3695 -- see feature_dimensions_mm.csv
    ("07_RAILINGS" 0 (
      (1038.1679 5816.7939) (961.8321 5816.7939) (961.8321 5801.5267) (961.8321 5725.1908) (961.8321 5633.5878)
      (961.8321 5541.9847) (961.8321 5465.6489) (1038.1679 5465.6489)
    ))
    ; P3696 -- see feature_dimensions_mm.csv
    ("07_RAILINGS" 0 (
      (1038.1679 5465.6489) (1058.0153 5465.6489)
    ))
    ; P3697 -- see feature_dimensions_mm.csv
    ("07_RAILINGS" 0 (
      (1058.0153 5816.7939) (1129.771 5816.7939)
    ))
    ; P3698 -- see feature_dimensions_mm.csv
    ("07_RAILINGS" 0 (
      (1058.0153 5816.7939) (1058.0153 5465.6489)
    ))
    ; P3699 -- see feature_dimensions_mm.csv
    ("07_RAILINGS" 0 (
      (1058.0153 5465.6489) (1129.771 5465.6489)
    ))
    ; P3700 -- see feature_dimensions_mm.csv
    ("07_RAILINGS" 0 (
      (1129.771 5816.7939) (1149.6183 5816.7939)
    ))
    ; P3701 -- see feature_dimensions_mm.csv
    ("07_RAILINGS" 0 (
      (1129.771 5465.6489) (1129.771 5816.7939)
    ))
    ; P3702 -- see feature_dimensions_mm.csv
    ("07_RAILINGS" 0 (
      (1129.771 5465.6489) (1149.6183 5465.6489)
    ))
    ; P3703 -- see feature_dimensions_mm.csv
    ("07_RAILINGS" 0 (
      (1149.6183 5816.7939) (1221.374 5816.7939)
    ))
    ; P3704 -- see feature_dimensions_mm.csv
    ("07_RAILINGS" 0 (
      (1149.6183 5816.7939) (1149.6183 5465.6489)
    ))
    ; P3705 -- see feature_dimensions_mm.csv
    ("07_RAILINGS" 0 (
      (1149.6183 5465.6489) (1221.374 5465.6489)
    ))
    ; P3706 -- see feature_dimensions_mm.csv
    ("07_RAILINGS" 0 (
      (1221.374 5816.7939) (1241.2214 5816.7939)
    ))
    ; P3707 -- see feature_dimensions_mm.csv
    ("07_RAILINGS" 0 (
      (1221.374 5465.6489) (1221.374 5816.7939)
    ))
    ; P3708 -- see feature_dimensions_mm.csv
    ("07_RAILINGS" 0 (
      (1221.374 5465.6489) (1241.2214 5465.6489)
    ))
    ; P3709 -- see feature_dimensions_mm.csv
    ("07_RAILINGS" 0 (
      (1241.2214 5816.7939) (1312.9771 5816.7939)
    ))
    ; P3710 -- see feature_dimensions_mm.csv
    ("07_RAILINGS" 0 (
      (1241.2214 5816.7939) (1241.2214 5465.6489)
    ))
    ; P3711 -- see feature_dimensions_mm.csv
    ("07_RAILINGS" 0 (
      (1241.2214 5465.6489) (1312.9771 5465.6489)
    ))
    ; P3712 -- see feature_dimensions_mm.csv
    ("07_RAILINGS" 0 (
      (1312.9771 5816.7939) (1332.8244 5816.7939)
    ))
    ; P3713 -- see feature_dimensions_mm.csv
    ("07_RAILINGS" 0 (
      (1312.9771 5465.6489) (1312.9771 5816.7939)
    ))
    ; P3714 -- see feature_dimensions_mm.csv
    ("07_RAILINGS" 0 (
      (1312.9771 5465.6489) (1332.8244 5465.6489)
    ))
    ; P3715 -- see feature_dimensions_mm.csv
    ("07_RAILINGS" 0 (
      (1332.8244 5816.7939) (1358.7786 5816.7939) (1358.7786 5465.6489) (1332.8244 5465.6489)
    ))
    ; P3716 -- see feature_dimensions_mm.csv
    ("07_RAILINGS" 0 (
      (1332.8244 5816.7939) (1332.8244 5465.6489)
    ))
    ; P3717 -- see feature_dimensions_mm.csv
    ("07_RAILINGS" 0 (
      (2030.5344 4412.2137) (2030.5344 4427.4809) (2229.0076 4427.4809)
    ))
    ; P3718 -- see feature_dimensions_mm.csv
    ("07_RAILINGS" 0 (
      (3984.7328 3679.3893) (3984.7328 3633.5878) (1969.4656 3633.5878) (1969.4656 3679.3893) (1969.4656 4473.2824)
      (2045.8015 4473.2824) (2152.6718 4473.2824)
    ))
    ; P3719 -- see feature_dimensions_mm.csv
    ("07_RAILINGS" 0 (
      (2229.0076 4427.4809) (2259.542 4427.4809)
    ))
    ; P3720 -- see feature_dimensions_mm.csv
    ("07_RAILINGS" 0 (
      (2229.0076 3832.0611) (2229.0076 4412.2137) (2229.0076 4427.4809)
    ))
    ; P3721 -- see feature_dimensions_mm.csv
    ("07_RAILINGS" 0 (
      (2259.542 4427.4809) (2961.8321 4427.4809)
    ))
    ; P3722 -- see feature_dimensions_mm.csv
    ("07_RAILINGS" 0 (
      (2259.542 4427.4809) (2259.542 4412.2137)
    ))
    ; P3723 -- see feature_dimensions_mm.csv
    ("07_RAILINGS" 0 (
      (2961.8321 4427.4809) (2992.3664 4427.4809)
    ))
    ; P3724 -- see feature_dimensions_mm.csv
    ("07_RAILINGS" 0 (
      (2961.8321 4412.2137) (2961.8321 4427.4809)
    ))
    ; P3725 -- see feature_dimensions_mm.csv
    ("07_RAILINGS" 0 (
      (2992.3664 3832.0611) (2961.8321 3832.0611)
    ))
    ; P3726 -- see feature_dimensions_mm.csv
    ("07_RAILINGS" 0 (
      (2992.3664 4427.4809) (3725.1908 4427.4809)
    ))
    ; P3727 -- see feature_dimensions_mm.csv
    ("07_RAILINGS" 0 (
      (2992.3664 4427.4809) (2992.3664 4412.2137)
    ))
    ; P3728 -- see feature_dimensions_mm.csv
    ("07_RAILINGS" 0 (
      (3725.1908 4427.4809) (3755.7252 4427.4809)
    ))
    ; P3729 -- see feature_dimensions_mm.csv
    ("07_RAILINGS" 0 (
      (3725.1908 3832.0611) (3725.1908 4412.2137) (3725.1908 4427.4809)
    ))
    ; P3730 -- see feature_dimensions_mm.csv
    ("07_RAILINGS" 0 (
      (3755.7252 4427.4809) (3923.6641 4427.4809) (3923.6641 4412.2137) (3923.6641 3832.0611)
    ))
    ; P3731 -- see feature_dimensions_mm.csv
    ("07_RAILINGS" 0 (
      (3755.7252 4427.4809) (3755.7252 4412.2137) (3755.7252 3832.0611)
    ))
    ; P3732 -- see feature_dimensions_mm.csv
    ("07_RAILINGS" 0 (
      (3908.3969 4473.2824) (3984.7328 4473.2824)
    ))
    ; P3733 -- see feature_dimensions_mm.csv
    ("07_RAILINGS" 0 (
      (4595.4198 5816.7939) (4671.7557 5816.7939)
    ))
    ; P3734 -- see feature_dimensions_mm.csv
    ("07_RAILINGS" 0 (
      (4671.7557 5816.7939) (4691.6031 5816.7939)
    ))
    ; P3735 -- see feature_dimensions_mm.csv
    ("07_RAILINGS" 0 (
      (4671.7557 5465.6489) (4671.7557 5816.7939)
    ))
    ; P3736 -- see feature_dimensions_mm.csv
    ("07_RAILINGS" 0 (
      (4691.6031 5816.7939) (4763.3588 5816.7939)
    ))
    ; P3737 -- see feature_dimensions_mm.csv
    ("07_RAILINGS" 0 (
      (4691.6031 5816.7939) (4691.6031 5465.6489)
    ))
    ; P3738 -- see feature_dimensions_mm.csv
    ("07_RAILINGS" 0 (
      (4763.3588 5816.7939) (4783.2061 5816.7939)
    ))
    ; P3739 -- see feature_dimensions_mm.csv
    ("07_RAILINGS" 0 (
      (4763.3588 5465.6489) (4763.3588 5816.7939)
    ))
    ; P3740 -- see feature_dimensions_mm.csv
    ("07_RAILINGS" 0 (
      (4783.2061 5816.7939) (4854.9618 5816.7939)
    ))
    ; P3741 -- see feature_dimensions_mm.csv
    ("07_RAILINGS" 0 (
      (4783.2061 5816.7939) (4783.2061 5465.6489)
    ))
    ; P3742 -- see feature_dimensions_mm.csv
    ("07_RAILINGS" 0 (
      (4854.9618 5816.7939) (4874.8092 5816.7939)
    ))
    ; P3743 -- see feature_dimensions_mm.csv
    ("07_RAILINGS" 0 (
      (4854.9618 5465.6489) (4854.9618 5816.7939)
    ))
    ; P3744 -- see feature_dimensions_mm.csv
    ("07_RAILINGS" 0 (
      (4874.8092 5816.7939) (4946.5649 5816.7939)
    ))
    ; P3745 -- see feature_dimensions_mm.csv
    ("07_RAILINGS" 0 (
      (4874.8092 5816.7939) (4874.8092 5465.6489)
    ))
    ; P3746 -- see feature_dimensions_mm.csv
    ("07_RAILINGS" 0 (
      (4946.5649 5816.7939) (4966.4122 5816.7939)
    ))
    ; P3747 -- see feature_dimensions_mm.csv
    ("07_RAILINGS" 0 (
      (4946.5649 5465.6489) (4946.5649 5816.7939)
    ))
    ; P3748 -- see feature_dimensions_mm.csv
    ("07_RAILINGS" 0 (
      (4966.4122 5816.7939) (4992.3664 5816.7939)
    ))
    ; P3749 -- see feature_dimensions_mm.csv
    ("07_RAILINGS" 0 (
      (4966.4122 5816.7939) (4966.4122 5465.6489)
    ))
    ; P3750 -- see feature_dimensions_mm.csv
    ("07_RAILINGS" 0 (
      (10274.8092 3618.3206) (8687.0229 3618.3206)
    ))
    ; P3751 -- see feature_dimensions_mm.csv
    ("07_RAILINGS" 0 (
      (8778.626 3832.0611) (8778.626 4412.2137) (8793.8931 4412.2137)
    ))
    ; P3752 -- see feature_dimensions_mm.csv
    ("07_RAILINGS" 0 (
      (8793.8931 3832.0611) (8885.4962 3832.0611) (8946.5649 3832.0611) (8969.9389 3832.0611) (8996.4733 3832.0611)
      (9400.4733 3832.0611)
    ))
    ; P3753 -- see feature_dimensions_mm.csv
    ("07_RAILINGS" 0 (
      (9296.1832 4412.2137) (9238.1679 4412.2137)
    ))
    ; P3754 -- see feature_dimensions_mm.csv
    ("07_RAILINGS" 0 (
      (9427.0076 3832.0611) (9450.3817 3832.0611)
    ))
    ; P3755 -- see feature_dimensions_mm.csv
    ("07_RAILINGS" 0 (
      (9450.3817 3832.0611) (9465.6489 3832.0611)
    ))
    ; P3756 -- see feature_dimensions_mm.csv
    ("07_RAILINGS" 0 (
      (9450.3817 3832.0611) (9450.3817 4412.2137) (9465.6489 4412.2137)
    ))
    ; P3757 -- see feature_dimensions_mm.csv
    ("07_RAILINGS" 0 (
      (9473.2824 4412.2137) (9496.1832 4412.2137)
    ))
    ; P3758 -- see feature_dimensions_mm.csv
    ("07_RAILINGS" 0 (
      (9496.1832 3832.0611) (9473.2824 3832.0611)
    ))
    ; P3759 -- see feature_dimensions_mm.csv
    ("07_RAILINGS" 0 (
      (9601.5267 4412.2137) (9511.4504 4412.2137) (9503.8168 4412.2137) (9496.1832 4412.2137)
    ))
    ; P3760 -- see feature_dimensions_mm.csv
    ("07_RAILINGS" 0 (
      (9496.1832 4412.2137) (9496.1832 3832.0611)
    ))
    ; P3761 -- see feature_dimensions_mm.csv
    ("07_RAILINGS" 0 (
      (9496.1832 3832.0611) (9503.8168 3832.0611) (9511.4504 3832.0611) (9550.0916 3832.0611) (9576.626 3832.0611)
      (9980.626 3832.0611) (10007.1603 3832.0611) (10030.5344 3832.0611) (10091.6031 3832.0611) (10183.2061 3832.0611)
      (10198.4733 3832.0611) (10198.4733 4412.2137) (10183.2061 4412.2137) (10091.6031 4412.2137) (10030.5344 4412.2137)
      (9955.7252 4412.2137) (9876.3359 4412.2137) (9818.3206 4412.2137)
    ))
    ; P3762 -- see feature_dimensions_mm.csv
    ("07_RAILINGS" 0 (
      (9738.9313 4412.2137) (9680.916 4412.2137)
    ))
    ; P3763 -- see feature_dimensions_mm.csv
    ("07_RAILINGS" 0 (
      (10290.0763 5816.7939) (10366.4122 5816.7939)
    ))
    ; P3764 -- see feature_dimensions_mm.csv
    ("07_RAILINGS" 0 (
      (10290.0763 3633.5878) (10290.0763 3664.1221) (10290.0763 3740.458)
    ))
    ; P3765 -- see feature_dimensions_mm.csv
    ("07_RAILINGS" 0 (
      (10366.4122 5816.7939) (10386.2595 5816.7939)
    ))
    ; P3766 -- see feature_dimensions_mm.csv
    ("07_RAILINGS" 0 (
      (10366.4122 5465.6489) (10366.4122 5816.7939)
    ))
    ; P3767 -- see feature_dimensions_mm.csv
    ("07_RAILINGS" 0 (
      (10386.2595 5816.7939) (10458.0153 5816.7939)
    ))
    ; P3768 -- see feature_dimensions_mm.csv
    ("07_RAILINGS" 0 (
      (10386.2595 5816.7939) (10386.2595 5465.6489)
    ))
    ; P3769 -- see feature_dimensions_mm.csv
    ("07_RAILINGS" 0 (
      (10458.0153 5816.7939) (10477.8626 5816.7939)
    ))
    ; P3770 -- see feature_dimensions_mm.csv
    ("07_RAILINGS" 0 (
      (10458.0153 5465.6489) (10458.0153 5816.7939)
    ))
    ; P3771 -- see feature_dimensions_mm.csv
    ("07_RAILINGS" 0 (
      (10477.8626 5816.7939) (10549.6183 5816.7939)
    ))
    ; P3772 -- see feature_dimensions_mm.csv
    ("07_RAILINGS" 0 (
      (10477.8626 5816.7939) (10477.8626 5465.6489)
    ))
    ; P3773 -- see feature_dimensions_mm.csv
    ("07_RAILINGS" 0 (
      (10549.6183 5816.7939) (10569.4656 5816.7939)
    ))
    ; P3774 -- see feature_dimensions_mm.csv
    ("07_RAILINGS" 0 (
      (10549.6183 5465.6489) (10549.6183 5816.7939)
    ))
    ; P3775 -- see feature_dimensions_mm.csv
    ("07_RAILINGS" 0 (
      (10569.4656 5816.7939) (10641.2214 5816.7939)
    ))
    ; P3776 -- see feature_dimensions_mm.csv
    ("07_RAILINGS" 0 (
      (10569.4656 5816.7939) (10569.4656 5465.6489)
    ))
    ; P3777 -- see feature_dimensions_mm.csv
    ("07_RAILINGS" 0 (
      (10641.2214 5816.7939) (10661.0687 5816.7939)
    ))
    ; P3778 -- see feature_dimensions_mm.csv
    ("07_RAILINGS" 0 (
      (10641.2214 5465.6489) (10641.2214 5816.7939)
    ))
    ; P3779 -- see feature_dimensions_mm.csv
    ("07_RAILINGS" 0 (
      (10661.0687 5816.7939) (10687.0229 5816.7939)
    ))
    ; P3780 -- see feature_dimensions_mm.csv
    ("07_RAILINGS" 0 (
      (10661.0687 5816.7939) (10661.0687 5465.6489)
    ))
    ; P3781 -- see feature_dimensions_mm.csv
    ("07_RAILINGS" 0 (
      (11312.9771 4427.4809) (11343.5115 4427.4809)
    ))
    ; P3782 -- see feature_dimensions_mm.csv
    ("07_RAILINGS" 0 (
      (11312.9771 3832.0611) (11312.9771 4412.2137) (11312.9771 4427.4809)
    ))
    ; P3783 -- see feature_dimensions_mm.csv
    ("07_RAILINGS" 0 (
      (11312.9771 4427.4809) (11114.5038 4427.4809) (11114.5038 4412.2137) (11114.5038 3832.0611) (11129.771 3832.0611)
      (11236.6412 3832.0611) (11312.9771 3832.0611)
    ))
    ; P3784 -- see feature_dimensions_mm.csv
    ("07_RAILINGS" 0 (
      (11312.9771 3832.0611) (11343.5115 3832.0611) (12022.9008 3832.0611)
    ))
    ; P3785 -- see feature_dimensions_mm.csv
    ("07_RAILINGS" 0 (
      (11343.5115 4427.4809) (12045.8015 4427.4809)
    ))
    ; P3786 -- see feature_dimensions_mm.csv
    ("07_RAILINGS" 0 (
      (11343.5115 4427.4809) (11343.5115 4412.2137)
    ))
    ; P3787 -- see feature_dimensions_mm.csv
    ("07_RAILINGS" 0 (
      (12045.8015 4427.4809) (12076.3359 4427.4809)
    ))
    ; P3788 -- see feature_dimensions_mm.csv
    ("07_RAILINGS" 0 (
      (12045.8015 4412.2137) (12045.8015 4427.4809)
    ))
    ; P3789 -- see feature_dimensions_mm.csv
    ("07_RAILINGS" 0 (
      (12045.8015 3832.0611) (12076.3359 3832.0611) (12099.2366 3832.0611) (12778.626 3832.0611)
    ))
    ; P3790 -- see feature_dimensions_mm.csv
    ("07_RAILINGS" 0 (
      (12076.3359 4427.4809) (12809.1603 4427.4809)
    ))
    ; P3791 -- see feature_dimensions_mm.csv
    ("07_RAILINGS" 0 (
      (12076.3359 4427.4809) (12076.3359 4412.2137)
    ))
    ; P3792 -- see feature_dimensions_mm.csv
    ("07_RAILINGS" 0 (
      (12099.2366 4473.2824) (12296.9008 4473.2824) (12330.2137 4473.2824) (12352.8397 4473.2824) (12408.6565 4473.2824)
      (12429.5267 4473.2824) (12455.9695 4473.2824) (12476.8397 4473.2824) (12532.6565 4473.2824) (12555.2824 4473.2824)
      (12588.5954 4473.2824)
    ))
    ; P3793 -- see feature_dimensions_mm.csv
    ("07_RAILINGS" 0 (
      (12809.1603 4427.4809) (12839.6947 4427.4809)
    ))
    ; P3794 -- see feature_dimensions_mm.csv
    ("07_RAILINGS" 0 (
      (12839.6947 4427.4809) (12839.6947 4412.2137) (12839.6947 3832.0611) (12809.1603 3832.0611) (12809.1603 4412.2137)
      (12809.1603 4427.4809)
    ))
    ; P3795 -- see feature_dimensions_mm.csv
    ("07_RAILINGS" 0 (
      (12839.6947 4427.4809) (13007.6336 4427.4809) (13007.6336 4412.2137) (13007.6336 3832.0611)
    ))
    ; P3796 -- see feature_dimensions_mm.csv
    ("07_RAILINGS" 0 (
      (13068.7023 4473.2824) (13068.7023 3679.3893)
    ))
    ; P3797 -- see feature_dimensions_mm.csv
    ("08_STEPS" 0 (
      (4152.6718 442.7481) (4167.9389 442.7481) (4167.9389 351.145) (3221.374 351.145) (3221.374 442.7481)
    ))
    ; P3798 -- see feature_dimensions_mm.csv
    ("08_STEPS" 0 (
      (10595.4198 122.1374) (10290.0763 122.1374) (8671.7557 122.1374) (8335.8779 122.1374)
    ))
    ; P3799 -- see feature_dimensions_mm.csv
    ("08_STEPS" 0 (
      (10595.4198 122.1374) (10778.626 122.1374) (10778.626 15.2672) (10290.0763 15.2672) (8671.7557 15.2672)
      (8152.6718 15.2672) (8152.6718 122.1374) (8335.8779 122.1374)
    ))
    ; P3800 -- see feature_dimensions_mm.csv
    ("08_STEPS" 0 (
      (8335.8779 122.1374) (8335.8779 213.7405) (8519.084 213.7405)
    ))
    ; P3801 -- see feature_dimensions_mm.csv
    ("08_STEPS" 0 (
      (10412.2137 213.7405) (10290.0763 213.7405) (8671.7557 213.7405) (8519.084 213.7405)
    ))
    ; P3802 -- see feature_dimensions_mm.csv
    ("08_STEPS" 0 (
      (8519.084 213.7405) (8519.084 290.0763) (8519.084 305.3435) (8702.2901 305.3435)
    ))
    ; P3803 -- see feature_dimensions_mm.csv
    ("08_STEPS" 0 (
      (10229.0076 305.3435) (8702.2901 305.3435)
    ))
    ; P3804 -- see feature_dimensions_mm.csv
    ("08_STEPS" 0 (
      (8702.2901 305.3435) (8702.2901 320.6107) (8702.2901 396.9466) (8748.0916 396.9466) (8839.6947 396.9466)
      (8916.0305 396.9466) (10076.3359 396.9466) (10152.6718 396.9466) (10229.0076 396.9466) (10229.0076 320.6107)
      (10229.0076 305.3435)
    ))
    ; P3805 -- see feature_dimensions_mm.csv
    ("08_STEPS" 0 (
      (10229.0076 305.3435) (10412.2137 305.3435) (10412.2137 290.0763) (10412.2137 213.7405)
    ))
    ; P3806 -- see feature_dimensions_mm.csv
    ("08_STEPS" 0 (
      (10412.2137 213.7405) (10595.4198 213.7405) (10595.4198 122.1374)
    ))
    ; P3807 -- see feature_dimensions_mm.csv
    ("08_STEPS" 1 (
      (-2412.2137 -15.2672) (16213.7405 -15.2672) (16213.7405 -122.1374) (-2412.2137 -122.1374)
    ))
    ; P3808 -- see feature_dimensions_mm.csv
    ("08_STEPS" 1 (
      (2564.8855 137.4046) (4824.4275 137.4046) (4824.4275 45.8015) (2564.8855 45.8015)
    ))
    ; P3809 -- see feature_dimensions_mm.csv
    ("08_STEPS" 1 (
      (2793.8931 244.2748) (4610.687 244.2748) (4610.687 152.6718) (2793.8931 152.6718)
    ))
    ; P3810 -- see feature_dimensions_mm.csv
    ("08_STEPS" 1 (
      (3007.6336 335.8779) (4396.9466 335.8779) (4396.9466 259.542) (3007.6336 259.542)
    ))
  ))
(princ "\nClean facade loaded. Type PALACE to draw, or PALACEINFO for help.")
(princ)

(setq PALC:SIZES '(
  ("OVERALL_WIDTH" 14000 nil)
  ("TOWER_HEIGHT" nil 10611)
  ("MIDDLE_CROWN" nil 8641)
  ("SIDE_CROWNS" nil 8076)
  ("BELT_CORNICE" nil 3298)
  ("LEFT_DOOR" 931 2046)
  ("CENTRAL_DOOR" 947 1939)
  ("LEFT_BALCONY" 1863 2000)
  ("RIGHT_BALCONY" 1863 2000)
  ("RECESS_OPENING" 1389 1893)
  ("NARROW_TALL_WINDOWS" 901 4748)
  ("MIDDLE_TALL_WINDOW" 1221 4748)
  ("GROUND_ROSE_WINDOWS" 1221 1786)
  ("LEFT_WING" 4031 nil)
  ("RIGHT_WING" 3542 nil)
  ("CENTRAL_BAY" 3679 nil)
))
