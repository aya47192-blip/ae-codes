; Geometric facade repair: genuine LINE and ARC architecture; vegetation removed and concealed architectural lines restored.
; APPLOAD, then FACADE_NOPLANTS. Data is embedded; estimated millimetres.
(setq FNP:DATA '(
((0 . "LINE") (100 . "AcDbEntity") (8 . "GROUND") (62 . 7) (370 . 13) (100 . "AcDbLine") (10 0.0 0.0 0.0) (11
610.8597285068 0.0 0.0))
((0 . "LINE") (100 . "AcDbEntity") (8 . "GROUND") (62 . 7) (370 . 13) (100 . "AcDbLine") (10 610.8597285068 0.0 0.0) (11
2782.8054298643 0.0 0.0))
((0 . "LINE") (100 . "AcDbEntity") (8 . "GROUND") (62 . 7) (370 . 13) (100 . "AcDbLine") (10 2782.8054298643 0.0 0.0)
(11 2816.742081448 0.0 0.0))
((0 . "LINE") (100 . "AcDbEntity") (8 . "GROUND") (62 . 7) (370 . 13) (100 . "AcDbLine") (10 2816.742081448 0.0 0.0) (11
7873.3031674208 0.0 0.0))
((0 . "LINE") (100 . "AcDbEntity") (8 . "GROUND") (62 . 7) (370 . 13) (100 . "AcDbLine") (10 7873.3031674208 0.0 0.0)
(11 7929.8642533937 0.0 0.0))
((0 . "LINE") (100 . "AcDbEntity") (8 . "ARCH") (62 . 7) (370 . 13) (100 . "AcDbLine") (10 7929.8642533937 0.0 0.0) (11
9547.5113122172 0.0 0.0))
((0 . "LINE") (100 . "AcDbEntity") (8 . "GROUND") (62 . 7) (370 . 13) (100 . "AcDbLine") (10 9547.5113122172 0.0 0.0)
(11 10452.4886877828 0.0 0.0))
((0 . "LINE") (100 . "AcDbEntity") (8 . "GROUND") (62 . 7) (370 . 13) (100 . "AcDbLine") (10 10452.4886877828 0.0 0.0)
(11 12036.1990950226 0.0 0.0))
((0 . "LINE") (100 . "AcDbEntity") (8 . "GROUND") (62 . 7) (370 . 13) (100 . "AcDbLine") (10 12036.1990950226 0.0 0.0)
(11 12115.3846153846 0.0 0.0))
((0 . "LINE") (100 . "AcDbEntity") (8 . "ARCH") (62 . 7) (370 . 13) (100 . "AcDbLine") (10 12115.3846153846 0.0 0.0) (11
17183.257918552 0.0 0.0))
((0 . "LINE") (100 . "AcDbEntity") (8 . "GROUND") (62 . 7) (370 . 13) (100 . "AcDbLine") (10 17183.257918552 0.0 0.0)
(11 17239.8190045249 0.0 0.0))
((0 . "LINE") (100 . "AcDbEntity") (8 . "GROUND") (62 . 7) (370 . 13) (100 . "AcDbLine") (10 17239.8190045249 0.0 0.0)
(11 19423.0769230769 0.0 0.0))
((0 . "LINE") (100 . "AcDbEntity") (8 . "GROUND") (62 . 7) (370 . 13) (100 . "AcDbLine") (10 19423.0769230769 0.0 0.0)
(11 19988.6877828054 0.0 0.0))
((0 . "LINE") (100 . "AcDbEntity") (8 . "ARCH") (62 . 7) (370 . 13) (100 . "AcDbLine") (10 610.8597285068 180.9954751131
0.0) (11 644.7963800905 180.9954751131 0.0))
((0 . "LINE") (100 . "AcDbEntity") (8 . "ARCH") (62 . 7) (370 . 13) (100 . "AcDbLine") (10 644.7963800905 180.9954751131
0.0) (11 2782.8054298643 180.9954751131 0.0))
((0 . "LINE") (100 . "AcDbEntity") (8 . "ARCH") (62 . 7) (370 . 13) (100 . "AcDbLine") (10 2782.8054298643
180.9954751131 0.0) (11 2782.8054298643 0.0 0.0))
((0 . "LINE") (100 . "AcDbEntity") (8 . "ARCH") (62 . 7) (370 . 13) (100 . "AcDbLine") (10 610.8597285068 0.0 0.0) (11
610.8597285068 180.9954751131 0.0))
((0 . "LINE") (100 . "AcDbEntity") (8 . "ARCH") (62 . 7) (370 . 13) (100 . "AcDbLine") (10 17239.8190045249
180.9954751131 0.0) (11 19389.1402714932 180.9954751131 0.0))
((0 . "LINE") (100 . "AcDbEntity") (8 . "ARCH") (62 . 7) (370 . 13) (100 . "AcDbLine") (10 19389.1402714932
180.9954751131 0.0) (11 19423.0769230769 180.9954751131 0.0))
((0 . "LINE") (100 . "AcDbEntity") (8 . "ARCH") (62 . 7) (370 . 13) (100 . "AcDbLine") (10 19423.0769230769
180.9954751131 0.0) (11 19423.0769230769 0.0 0.0))
((0 . "LINE") (100 . "AcDbEntity") (8 . "ARCH") (62 . 7) (370 . 13) (100 . "AcDbLine") (10 17239.8190045249 0.0 0.0) (11
17239.8190045249 180.9954751131 0.0))
((0 . "LINE") (100 . "AcDbEntity") (8 . "ARCH") (62 . 7) (370 . 13) (100 . "AcDbLine") (10 2816.742081448 214.9321266968
0.0) (11 7873.3031674208 214.9321266968 0.0))
((0 . "LINE") (100 . "AcDbEntity") (8 . "ARCH") (62 . 7) (370 . 13) (100 . "AcDbLine") (10 7873.3031674208
214.9321266968 0.0) (11 7873.3031674208 158.371040724 0.0))
((0 . "LINE") (100 . "AcDbEntity") (8 . "ARCH") (62 . 7) (370 . 13) (100 . "AcDbLine") (10 7873.3031674208 158.371040724
0.0) (11 7873.3031674208 0.0 0.0))
((0 . "LINE") (100 . "AcDbEntity") (8 . "ARCH") (62 . 7) (370 . 13) (100 . "AcDbLine") (10 2816.742081448 0.0 0.0) (11
2816.742081448 158.371040724 0.0))
((0 . "LINE") (100 . "AcDbEntity") (8 . "ARCH") (62 . 7) (370 . 13) (100 . "AcDbLine") (10 2816.742081448 158.371040724
0.0) (11 2816.742081448 214.9321266968 0.0))
((0 . "LINE") (100 . "AcDbEntity") (8 . "ARCH") (62 . 7) (370 . 13) (100 . "AcDbLine") (10 2816.742081448 158.371040724
0.0) (11 7873.3031674208 158.371040724 0.0))
((0 . "LINE") (100 . "AcDbEntity") (8 . "ARCH") (62 . 7) (370 . 13) (100 . "AcDbLine") (10 12115.3846153846
214.9321266968 0.0) (11 17183.257918552 214.9321266968 0.0))
((0 . "LINE") (100 . "AcDbEntity") (8 . "ARCH") (62 . 7) (370 . 13) (100 . "AcDbLine") (10 17183.257918552
214.9321266968 0.0) (11 17183.257918552 158.371040724 0.0))
((0 . "LINE") (100 . "AcDbEntity") (8 . "ARCH") (62 . 7) (370 . 13) (100 . "AcDbLine") (10 17183.257918552 158.371040724
0.0) (11 17183.257918552 0.0 0.0))
((0 . "LINE") (100 . "AcDbEntity") (8 . "ARCH") (62 . 7) (370 . 13) (100 . "AcDbLine") (10 12115.3846153846 0.0 0.0) (11
12115.3846153846 158.371040724 0.0))
((0 . "LINE") (100 . "AcDbEntity") (8 . "ARCH") (62 . 7) (370 . 13) (100 . "AcDbLine") (10 12115.3846153846
158.371040724 0.0) (11 12115.3846153846 214.9321266968 0.0))
((0 . "LINE") (100 . "AcDbEntity") (8 . "ARCH") (62 . 7) (370 . 13) (100 . "AcDbLine") (10 12115.3846153846
158.371040724 0.0) (11 17183.257918552 158.371040724 0.0))
((0 . "LINE") (100 . "AcDbEntity") (8 . "ARCH") (62 . 7) (370 . 13) (100 . "AcDbLine") (10 644.7963800905
5622.1719457014 0.0) (11 644.7963800905 5599.5475113122 0.0))
((0 . "LINE") (100 . "AcDbEntity") (8 . "ARCH") (62 . 7) (370 . 13) (100 . "AcDbLine") (10 644.7963800905
5599.5475113122 0.0) (11 644.7963800905 4819.0045248869 0.0))
((0 . "LINE") (100 . "AcDbEntity") (8 . "ARCH") (62 . 7) (370 . 13) (100 . "AcDbLine") (10 644.7963800905
4819.0045248869 0.0) (11 644.7963800905 4457.0135746606 0.0))
((0 . "LINE") (100 . "AcDbEntity") (8 . "ARCH") (62 . 7) (370 . 13) (100 . "AcDbLine") (10 644.7963800905
4457.0135746606 0.0) (11 644.7963800905 2997.7375565611 0.0))
((0 . "LINE") (100 . "AcDbEntity") (8 . "ARCH") (62 . 7) (370 . 13) (100 . "AcDbLine") (10 644.7963800905
2805.4298642534 0.0) (11 644.7963800905 2047.5113122172 0.0))
((0 . "LINE") (100 . "AcDbEntity") (8 . "ARCH") (62 . 7) (370 . 13) (100 . "AcDbLine") (10 644.7963800905
2047.5113122172 0.0) (11 644.7963800905 1651.5837104072 0.0))
((0 . "LINE") (100 . "AcDbEntity") (8 . "ARCH") (62 . 7) (370 . 13) (100 . "AcDbLine") (10 644.7963800905
1651.5837104072 0.0) (11 644.7963800905 180.9954751131 0.0))
((0 . "LINE") (100 . "AcDbEntity") (8 . "ARCH") (62 . 7) (370 . 13) (100 . "AcDbLine") (10 2782.8054298643
5622.1719457014 0.0) (11 2782.8054298643 5610.8597285068 0.0))
((0 . "LINE") (100 . "AcDbEntity") (8 . "ARCH") (62 . 7) (370 . 13) (100 . "AcDbLine") (10 2782.8054298643
5610.8597285068 0.0) (11 2782.8054298643 5599.5475113122 0.0))
((0 . "LINE") (100 . "AcDbEntity") (8 . "ARCH") (62 . 7) (370 . 13) (100 . "AcDbLine") (10 2782.8054298643
5599.5475113122 0.0) (11 2782.8054298643 4819.0045248869 0.0))
((0 . "LINE") (100 . "AcDbEntity") (8 . "ARCH") (62 . 7) (370 . 13) (100 . "AcDbLine") (10 2782.8054298643
4819.0045248869 0.0) (11 2782.8054298643 4457.0135746606 0.0))
((0 . "LINE") (100 . "AcDbEntity") (8 . "ARCH") (62 . 7) (370 . 13) (100 . "AcDbLine") (10 2782.8054298643
4457.0135746606 0.0) (11 2782.8054298643 3789.592760181 0.0))
((0 . "LINE") (100 . "AcDbEntity") (8 . "ARCH") (62 . 7) (370 . 13) (100 . "AcDbLine") (10 2782.8054298643
2805.4298642534 0.0) (11 2782.8054298643 2047.5113122172 0.0))
((0 . "LINE") (100 . "AcDbEntity") (8 . "ARCH") (62 . 7) (370 . 13) (100 . "AcDbLine") (10 2782.8054298643
2047.5113122172 0.0) (11 2782.8054298643 1651.5837104072 0.0))
((0 . "LINE") (100 . "AcDbEntity") (8 . "ARCH") (62 . 7) (370 . 13) (100 . "AcDbLine") (10 2782.8054298643
1651.5837104072 0.0) (11 2782.8054298643 180.9954751131 0.0))
((0 . "LINE") (100 . "AcDbEntity") (8 . "ARCH") (62 . 7) (370 . 13) (100 . "AcDbLine") (10 610.8597285068
2997.7375565611 0.0) (11 644.7963800905 2997.7375565611 0.0))
((0 . "LINE") (100 . "AcDbEntity") (8 . "ARCH") (62 . 7) (370 . 13) (100 . "AcDbLine") (10 644.7963800905
2997.7375565611 0.0) (11 2782.8054298643 2997.7375565611 0.0))
((0 . "LINE") (100 . "AcDbEntity") (8 . "ARCH") (62 . 7) (370 . 13) (100 . "AcDbLine") (10 2782.8054298643
2997.7375565611 0.0) (11 2782.8054298643 2861.9909502262 0.0))
((0 . "LINE") (100 . "AcDbEntity") (8 . "ARCH") (62 . 7) (370 . 13) (100 . "AcDbLine") (10 2782.8054298643
2861.9909502262 0.0) (11 2782.8054298643 2805.4298642534 0.0))
((0 . "LINE") (100 . "AcDbEntity") (8 . "ARCH") (62 . 7) (370 . 13) (100 . "AcDbLine") (10 2782.8054298643
2805.4298642534 0.0) (11 644.7963800905 2805.4298642534 0.0))
((0 . "LINE") (100 . "AcDbEntity") (8 . "ARCH") (62 . 7) (370 . 13) (100 . "AcDbLine") (10 644.7963800905
2805.4298642534 0.0) (11 610.8597285068 2805.4298642534 0.0))
((0 . "LINE") (100 . "AcDbEntity") (8 . "ARCH") (62 . 7) (370 . 13) (100 . "AcDbLine") (10 610.8597285068
2805.4298642534 0.0) (11 610.8597285068 2861.9909502262 0.0))
((0 . "LINE") (100 . "AcDbEntity") (8 . "ARCH") (62 . 7) (370 . 13) (100 . "AcDbLine") (10 610.8597285068
2861.9909502262 0.0) (11 610.8597285068 2997.7375565611 0.0))
((0 . "LINE") (100 . "AcDbEntity") (8 . "ARCH") (62 . 7) (370 . 13) (100 . "AcDbLine") (10 610.8597285068
2861.9909502262 0.0) (11 2782.8054298643 2861.9909502262 0.0))
((0 . "LINE") (100 . "AcDbEntity") (8 . "ARCH") (62 . 7) (370 . 13) (100 . "AcDbLine") (10 644.7963800905
4819.0045248869 0.0) (11 1018.0995475113 4819.0045248869 0.0))
((0 . "LINE") (100 . "AcDbEntity") (8 . "ARCH") (62 . 7) (370 . 13) (100 . "AcDbLine") (10 2680.9954751131
4819.0045248869 0.0) (11 2782.8054298643 4819.0045248869 0.0))
((0 . "LINE") (100 . "AcDbEntity") (8 . "ARCH") (62 . 7) (370 . 13) (100 . "AcDbLine") (10 644.7963800905
4457.0135746606 0.0) (11 1018.0995475113 4457.0135746606 0.0))
((0 . "LINE") (100 . "AcDbEntity") (8 . "ARCH") (62 . 7) (370 . 13) (100 . "AcDbLine") (10 2680.9954751131
4457.0135746606 0.0) (11 2782.8054298643 4457.0135746606 0.0))
((0 . "LINE") (100 . "AcDbEntity") (8 . "ARCH") (62 . 7) (370 . 13) (100 . "AcDbLine") (10 644.7963800905
2047.5113122172 0.0) (11 1018.0995475113 2047.5113122172 0.0))
((0 . "LINE") (100 . "AcDbEntity") (8 . "ARCH") (62 . 7) (370 . 13) (100 . "AcDbLine") (10 2680.9954751131
2047.5113122172 0.0) (11 2782.8054298643 2047.5113122172 0.0))
((0 . "LINE") (100 . "AcDbEntity") (8 . "ARCH") (62 . 7) (370 . 13) (100 . "AcDbLine") (10 644.7963800905
1651.5837104072 0.0) (11 1018.0995475113 1651.5837104072 0.0))
((0 . "LINE") (100 . "AcDbEntity") (8 . "ARCH") (62 . 7) (370 . 13) (100 . "AcDbLine") (10 2680.9954751131
1651.5837104072 0.0) (11 2782.8054298643 1651.5837104072 0.0))
((0 . "LINE") (100 . "AcDbEntity") (8 . "ARCH") (62 . 7) (370 . 13) (100 . "AcDbLine") (10 644.7963800905
5882.3529411765 0.0) (11 644.7963800905 5890.0783597285 0.0))
((0 . "LINE") (100 . "AcDbEntity") (8 . "ARCH") (62 . 7) (370 . 13) (100 . "AcDbLine") (10 644.7963800905
5890.0783597285 0.0) (11 644.7963800905 6481.9004524887 0.0))
((0 . "LINE") (100 . "AcDbEntity") (8 . "ARCH") (62 . 7) (370 . 13) (100 . "AcDbLine") (10 644.7963800905
6481.9004524887 0.0) (11 1606.334841629 6481.9004524887 0.0))
((0 . "LINE") (100 . "AcDbEntity") (8 . "ARCH") (62 . 7) (370 . 13) (100 . "AcDbLine") (10 1606.334841629
6481.9004524887 0.0) (11 1606.334841629 6334.8416289593 0.0))
((0 . "LINE") (100 . "AcDbEntity") (8 . "ARCH") (62 . 7) (370 . 13) (100 . "AcDbLine") (10 1606.334841629
6334.8416289593 0.0) (11 1889.1402714932 6334.8416289593 0.0))
((0 . "LINE") (100 . "AcDbEntity") (8 . "ARCH") (62 . 7) (370 . 13) (100 . "AcDbLine") (10 1889.1402714932
6334.8416289593 0.0) (11 1889.1402714932 6481.9004524887 0.0))
((0 . "LINE") (100 . "AcDbEntity") (8 . "ARCH") (62 . 7) (370 . 13) (100 . "AcDbLine") (10 1889.1402714932
6481.9004524887 0.0) (11 2726.2443438914 6481.9004524887 0.0))
((0 . "LINE") (100 . "AcDbEntity") (8 . "ARCH") (62 . 7) (370 . 13) (100 . "AcDbLine") (10 2726.2443438914
6481.9004524887 0.0) (11 2782.8054298643 6481.9004524887 0.0))
((0 . "LINE") (100 . "AcDbEntity") (8 . "ARCH") (62 . 7) (370 . 13) (100 . "AcDbLine") (10 622.1719457014
6481.9004524887 0.0) (11 622.1719457014 6549.7737556561 0.0))
((0 . "LINE") (100 . "AcDbEntity") (8 . "ARCH") (62 . 7) (370 . 13) (100 . "AcDbLine") (10 622.1719457014
6549.7737556561 0.0) (11 1674.2081447964 6549.7737556561 0.0))
((0 . "LINE") (100 . "AcDbEntity") (8 . "ARCH") (62 . 7) (370 . 13) (100 . "AcDbLine") (10 1674.2081447964
6549.7737556561 0.0) (11 1674.2081447964 6391.4027149321 0.0))
((0 . "LINE") (100 . "AcDbEntity") (8 . "ARCH") (62 . 7) (370 . 13) (100 . "AcDbLine") (10 1674.2081447964
6391.4027149321 0.0) (11 1832.5791855204 6391.4027149321 0.0))
((0 . "LINE") (100 . "AcDbEntity") (8 . "ARCH") (62 . 7) (370 . 13) (100 . "AcDbLine") (10 1832.5791855204
6391.4027149321 0.0) (11 1832.5791855204 6549.7737556561 0.0))
((0 . "LINE") (100 . "AcDbEntity") (8 . "ARCH") (62 . 7) (370 . 13) (100 . "AcDbLine") (10 1832.5791855204
6549.7737556561 0.0) (11 2726.2443438914 6549.7737556561 0.0))
((0 . "LINE") (100 . "AcDbEntity") (8 . "ARCH") (62 . 7) (370 . 13) (100 . "AcDbLine") (10 2726.2443438914
6549.7737556561 0.0) (11 2782.8054298643 6549.7737556561 0.0))
((0 . "LINE") (100 . "AcDbEntity") (8 . "ARCH") (62 . 7) (370 . 13) (100 . "AcDbLine") (10 441.1764705882
5803.1674208145 0.0) (11 644.7963800905 5890.0783597285 0.0))
((0 . "LINE") (100 . "AcDbEntity") (8 . "ARCH") (62 . 7) (370 . 13) (100 . "AcDbLine") (10 644.7963800905
5890.0783597285 0.0) (11 1368.778280543 6199.0950226244 0.0))
((0 . "LINE") (100 . "AcDbEntity") (8 . "ARCH") (62 . 7) (370 . 13) (100 . "AcDbLine") (10 1368.778280543
6199.0950226244 0.0) (11 2782.8054298643 6199.0950226244 0.0))
((0 . "LINE") (100 . "AcDbEntity") (8 . "ARCH") (62 . 7) (370 . 13) (100 . "AcDbLine") (10 441.1764705882
5803.1674208145 0.0) (11 441.1764705882 5757.9185520362 0.0))
((0 . "LINE") (100 . "AcDbEntity") (8 . "ARCH") (62 . 7) (370 . 13) (100 . "AcDbLine") (10 441.1764705882
5757.9185520362 0.0) (11 466.628959276 5746.6063348416 0.0))
((0 . "LINE") (100 . "AcDbEntity") (8 . "ARCH") (62 . 7) (370 . 13) (100 . "AcDbLine") (10 466.628959276 5746.6063348416
0.0) (11 542.9864253394 5712.6696832579 0.0))
((0 . "LINE") (100 . "AcDbEntity") (8 . "ARCH") (62 . 7) (370 . 13) (100 . "AcDbLine") (10 542.9864253394
5712.6696832579 0.0) (11 542.9864253394 5667.4208144796 0.0))
((0 . "LINE") (100 . "AcDbEntity") (8 . "ARCH") (62 . 7) (370 . 13) (100 . "AcDbLine") (10 542.9864253394
5667.4208144796 0.0) (11 588.2352941176 5667.4208144796 0.0))
((0 . "LINE") (100 . "AcDbEntity") (8 . "ARCH") (62 . 7) (370 . 13) (100 . "AcDbLine") (10 588.2352941176
5667.4208144796 0.0) (11 588.2352941176 5599.5475113122 0.0))
((0 . "LINE") (100 . "AcDbEntity") (8 . "ARCH") (62 . 7) (370 . 13) (100 . "AcDbLine") (10 588.2352941176
5599.5475113122 0.0) (11 644.7963800905 5599.5475113122 0.0))
((0 . "LINE") (100 . "AcDbEntity") (8 . "ARCH") (62 . 7) (370 . 13) (100 . "AcDbLine") (10 644.7963800905
5599.5475113122 0.0) (11 2782.8054298643 5599.5475113122 0.0))
((0 . "LINE") (100 . "AcDbEntity") (8 . "ARCH") (62 . 7) (370 . 13) (100 . "AcDbLine") (10 441.1764705882
5803.1674208145 0.0) (11 2782.8054298643 5803.1674208145 0.0))
((0 . "LINE") (100 . "AcDbEntity") (8 . "ARCH") (62 . 7) (370 . 13) (100 . "AcDbLine") (10 466.628959276 5746.6063348416
0.0) (11 2782.8054298643 5746.6063348416 0.0))
((0 . "LINE") (100 . "AcDbEntity") (8 . "ARCH") (62 . 7) (370 . 13) (100 . "AcDbLine") (10 588.2352941176
5667.4208144796 0.0) (11 2782.8054298643 5667.4208144796 0.0))
((0 . "LINE") (100 . "AcDbEntity") (8 . "ARCH") (62 . 7) (370 . 13) (100 . "AcDbLine") (10 17239.8190045249
5622.1719457014 0.0) (11 17239.8190045249 5610.8597285068 0.0))
((0 . "LINE") (100 . "AcDbEntity") (8 . "ARCH") (62 . 7) (370 . 13) (100 . "AcDbLine") (10 17239.8190045249
5610.8597285068 0.0) (11 17239.8190045249 5599.5475113122 0.0))
((0 . "LINE") (100 . "AcDbEntity") (8 . "ARCH") (62 . 7) (370 . 13) (100 . "AcDbLine") (10 17239.8190045249
5599.5475113122 0.0) (11 17239.8190045249 4819.0045248869 0.0))
((0 . "LINE") (100 . "AcDbEntity") (8 . "ARCH") (62 . 7) (370 . 13) (100 . "AcDbLine") (10 17239.8190045249
4819.0045248869 0.0) (11 17239.8190045249 4457.0135746606 0.0))
((0 . "LINE") (100 . "AcDbEntity") (8 . "ARCH") (62 . 7) (370 . 13) (100 . "AcDbLine") (10 17239.8190045249
4457.0135746606 0.0) (11 17239.8190045249 3789.592760181 0.0))
((0 . "LINE") (100 . "AcDbEntity") (8 . "ARCH") (62 . 7) (370 . 13) (100 . "AcDbLine") (10 17239.8190045249
3789.592760181 0.0) (11 17239.8190045249 3721.7194570136 0.0))
((0 . "LINE") (100 . "AcDbEntity") (8 . "ARCH") (62 . 7) (370 . 13) (100 . "AcDbLine") (10 17239.8190045249
3721.7194570136 0.0) (11 17239.8190045249 3597.2850678733 0.0))
((0 . "LINE") (100 . "AcDbEntity") (8 . "ARCH") (62 . 7) (370 . 13) (100 . "AcDbLine") (10 17239.8190045249
3597.2850678733 0.0) (11 17239.8190045249 3585.9728506787 0.0))
((0 . "LINE") (100 . "AcDbEntity") (8 . "ARCH") (62 . 7) (370 . 13) (100 . "AcDbLine") (10 17239.8190045249
3585.9728506787 0.0) (11 17239.8190045249 2997.7375565611 0.0))
((0 . "LINE") (100 . "AcDbEntity") (8 . "ARCH") (62 . 7) (370 . 13) (100 . "AcDbLine") (10 17239.8190045249
2805.4298642534 0.0) (11 17239.8190045249 2047.5113122172 0.0))
((0 . "LINE") (100 . "AcDbEntity") (8 . "ARCH") (62 . 7) (370 . 13) (100 . "AcDbLine") (10 17239.8190045249
2047.5113122172 0.0) (11 17239.8190045249 1651.5837104072 0.0))
((0 . "LINE") (100 . "AcDbEntity") (8 . "ARCH") (62 . 7) (370 . 13) (100 . "AcDbLine") (10 17239.8190045249
1651.5837104072 0.0) (11 17239.8190045249 180.9954751131 0.0))
((0 . "LINE") (100 . "AcDbEntity") (8 . "ARCH") (62 . 7) (370 . 13) (100 . "AcDbLine") (10 19389.1402714932
5622.1719457014 0.0) (11 19389.1402714932 5599.5475113122 0.0))
((0 . "LINE") (100 . "AcDbEntity") (8 . "ARCH") (62 . 7) (370 . 13) (100 . "AcDbLine") (10 19389.1402714932
5599.5475113122 0.0) (11 19389.1402714932 4819.0045248869 0.0))
((0 . "LINE") (100 . "AcDbEntity") (8 . "ARCH") (62 . 7) (370 . 13) (100 . "AcDbLine") (10 19389.1402714932
4819.0045248869 0.0) (11 19389.1402714932 4457.0135746606 0.0))
((0 . "LINE") (100 . "AcDbEntity") (8 . "ARCH") (62 . 7) (370 . 13) (100 . "AcDbLine") (10 19389.1402714932
4457.0135746606 0.0) (11 19389.1402714932 3789.592760181 0.0))
((0 . "LINE") (100 . "AcDbEntity") (8 . "ARCH") (62 . 7) (370 . 13) (100 . "AcDbLine") (10 19389.1402714932
2805.4298642534 0.0) (11 19389.1402714932 2047.5113122172 0.0))
((0 . "LINE") (100 . "AcDbEntity") (8 . "ARCH") (62 . 7) (370 . 13) (100 . "AcDbLine") (10 19389.1402714932
2047.5113122172 0.0) (11 19389.1402714932 1651.5837104072 0.0))
((0 . "LINE") (100 . "AcDbEntity") (8 . "ARCH") (62 . 7) (370 . 13) (100 . "AcDbLine") (10 19389.1402714932
1651.5837104072 0.0) (11 19389.1402714932 180.9954751131 0.0))
((0 . "LINE") (100 . "AcDbEntity") (8 . "ARCH") (62 . 7) (370 . 13) (100 . "AcDbLine") (10 17205.8823529412
2997.7375565611 0.0) (11 17239.8190045249 2997.7375565611 0.0))
((0 . "LINE") (100 . "AcDbEntity") (8 . "ARCH") (62 . 7) (370 . 13) (100 . "AcDbLine") (10 17239.8190045249
2997.7375565611 0.0) (11 19389.1402714932 2997.7375565611 0.0))
((0 . "LINE") (100 . "AcDbEntity") (8 . "ARCH") (62 . 7) (370 . 13) (100 . "AcDbLine") (10 19389.1402714932
2997.7375565611 0.0) (11 19389.1402714932 2861.9909502262 0.0))
((0 . "LINE") (100 . "AcDbEntity") (8 . "ARCH") (62 . 7) (370 . 13) (100 . "AcDbLine") (10 19389.1402714932
2861.9909502262 0.0) (11 19389.1402714932 2805.4298642534 0.0))
((0 . "LINE") (100 . "AcDbEntity") (8 . "ARCH") (62 . 7) (370 . 13) (100 . "AcDbLine") (10 19389.1402714932
2805.4298642534 0.0) (11 17239.8190045249 2805.4298642534 0.0))
((0 . "LINE") (100 . "AcDbEntity") (8 . "ARCH") (62 . 7) (370 . 13) (100 . "AcDbLine") (10 17239.8190045249
2805.4298642534 0.0) (11 17205.8823529412 2805.4298642534 0.0))
((0 . "LINE") (100 . "AcDbEntity") (8 . "ARCH") (62 . 7) (370 . 13) (100 . "AcDbLine") (10 17205.8823529412
2805.4298642534 0.0) (11 17205.8823529412 2861.9909502262 0.0))
((0 . "LINE") (100 . "AcDbEntity") (8 . "ARCH") (62 . 7) (370 . 13) (100 . "AcDbLine") (10 17205.8823529412
2861.9909502262 0.0) (11 17205.8823529412 2997.7375565611 0.0))
((0 . "LINE") (100 . "AcDbEntity") (8 . "ARCH") (62 . 7) (370 . 13) (100 . "AcDbLine") (10 17205.8823529412
2861.9909502262 0.0) (11 17239.8190045249 2861.9909502262 0.0))
((0 . "LINE") (100 . "AcDbEntity") (8 . "ARCH") (62 . 7) (370 . 13) (100 . "AcDbLine") (10 17239.8190045249
2861.9909502262 0.0) (11 19389.1402714932 2861.9909502262 0.0))
((0 . "LINE") (100 . "AcDbEntity") (8 . "ARCH") (62 . 7) (370 . 13) (100 . "AcDbLine") (10 17239.8190045249
4819.0045248869 0.0) (11 17352.9411764706 4819.0045248869 0.0))
((0 . "LINE") (100 . "AcDbEntity") (8 . "ARCH") (62 . 7) (370 . 13) (100 . "AcDbLine") (10 19015.8371040724
4819.0045248869 0.0) (11 19389.1402714932 4819.0045248869 0.0))
((0 . "LINE") (100 . "AcDbEntity") (8 . "ARCH") (62 . 7) (370 . 13) (100 . "AcDbLine") (10 17239.8190045249
4457.0135746606 0.0) (11 17352.9411764706 4457.0135746606 0.0))
((0 . "LINE") (100 . "AcDbEntity") (8 . "ARCH") (62 . 7) (370 . 13) (100 . "AcDbLine") (10 19015.8371040724
4457.0135746606 0.0) (11 19389.1402714932 4457.0135746606 0.0))
((0 . "LINE") (100 . "AcDbEntity") (8 . "ARCH") (62 . 7) (370 . 13) (100 . "AcDbLine") (10 17239.8190045249
2047.5113122172 0.0) (11 17352.9411764706 2047.5113122172 0.0))
((0 . "LINE") (100 . "AcDbEntity") (8 . "ARCH") (62 . 7) (370 . 13) (100 . "AcDbLine") (10 19015.8371040724
2047.5113122172 0.0) (11 19389.1402714932 2047.5113122172 0.0))
((0 . "LINE") (100 . "AcDbEntity") (8 . "ARCH") (62 . 7) (370 . 13) (100 . "AcDbLine") (10 17239.8190045249
1651.5837104072 0.0) (11 17352.9411764706 1651.5837104072 0.0))
((0 . "LINE") (100 . "AcDbEntity") (8 . "ARCH") (62 . 7) (370 . 13) (100 . "AcDbLine") (10 19015.8371040724
1651.5837104072 0.0) (11 19389.1402714932 1651.5837104072 0.0))
((0 . "LINE") (100 . "AcDbEntity") (8 . "ARCH") (62 . 7) (370 . 13) (100 . "AcDbLine") (10 19389.1402714932
5871.0407239819 0.0) (11 19389.1402714932 5894.9067420814 0.0))
((0 . "LINE") (100 . "AcDbEntity") (8 . "ARCH") (62 . 7) (370 . 13) (100 . "AcDbLine") (10 19389.1402714932
5894.9067420814 0.0) (11 19389.1402714932 6481.9004524887 0.0))
((0 . "LINE") (100 . "AcDbEntity") (8 . "ARCH") (62 . 7) (370 . 13) (100 . "AcDbLine") (10 19389.1402714932
6481.9004524887 0.0) (11 18416.2895927602 6481.9004524887 0.0))
((0 . "LINE") (100 . "AcDbEntity") (8 . "ARCH") (62 . 7) (370 . 13) (100 . "AcDbLine") (10 18416.2895927602
6481.9004524887 0.0) (11 18416.2895927602 6334.8416289593 0.0))
((0 . "LINE") (100 . "AcDbEntity") (8 . "ARCH") (62 . 7) (370 . 13) (100 . "AcDbLine") (10 18416.2895927602
6334.8416289593 0.0) (11 18144.7963800905 6334.8416289593 0.0))
((0 . "LINE") (100 . "AcDbEntity") (8 . "ARCH") (62 . 7) (370 . 13) (100 . "AcDbLine") (10 18144.7963800905
6334.8416289593 0.0) (11 18144.7963800905 6481.9004524887 0.0))
((0 . "LINE") (100 . "AcDbEntity") (8 . "ARCH") (62 . 7) (370 . 13) (100 . "AcDbLine") (10 18144.7963800905
6481.9004524887 0.0) (11 17330.3167420814 6481.9004524887 0.0))
((0 . "LINE") (100 . "AcDbEntity") (8 . "ARCH") (62 . 7) (370 . 13) (100 . "AcDbLine") (10 17330.3167420814
6481.9004524887 0.0) (11 17239.8190045249 6481.9004524887 0.0))
((0 . "LINE") (100 . "AcDbEntity") (8 . "ARCH") (62 . 7) (370 . 13) (100 . "AcDbLine") (10 19423.0769230769
6481.9004524887 0.0) (11 19423.0769230769 6549.7737556561 0.0))
((0 . "LINE") (100 . "AcDbEntity") (8 . "ARCH") (62 . 7) (370 . 13) (100 . "AcDbLine") (10 19423.0769230769
6549.7737556561 0.0) (11 18371.0407239819 6549.7737556561 0.0))
((0 . "LINE") (100 . "AcDbEntity") (8 . "ARCH") (62 . 7) (370 . 13) (100 . "AcDbLine") (10 18371.0407239819
6549.7737556561 0.0) (11 18223.9819004525 6549.7737556561 0.0))
((0 . "LINE") (100 . "AcDbEntity") (8 . "ARCH") (62 . 7) (370 . 13) (100 . "AcDbLine") (10 18223.9819004525
6549.7737556561 0.0) (11 18223.9819004525 6391.4027149321 0.0))
((0 . "LINE") (100 . "AcDbEntity") (8 . "ARCH") (62 . 7) (370 . 13) (100 . "AcDbLine") (10 18223.9819004525
6391.4027149321 0.0) (11 18371.0407239819 6391.4027149321 0.0))
((0 . "LINE") (100 . "AcDbEntity") (8 . "ARCH") (62 . 7) (370 . 13) (100 . "AcDbLine") (10 18371.0407239819
6391.4027149321 0.0) (11 18371.0407239819 6549.7737556561 0.0))
((0 . "LINE") (100 . "AcDbEntity") (8 . "ARCH") (62 . 7) (370 . 13) (100 . "AcDbLine") (10 18223.9819004525
6549.7737556561 0.0) (11 17330.3167420814 6549.7737556561 0.0))
((0 . "LINE") (100 . "AcDbEntity") (8 . "ARCH") (62 . 7) (370 . 13) (100 . "AcDbLine") (10 17330.3167420814
6549.7737556561 0.0) (11 17239.8190045249 6549.7737556561 0.0))
((0 . "LINE") (100 . "AcDbEntity") (8 . "ARCH") (62 . 7) (370 . 13) (100 . "AcDbLine") (10 19604.07239819
5803.1674208145 0.0) (11 19389.1402714932 5894.9067420814 0.0))
((0 . "LINE") (100 . "AcDbEntity") (8 . "ARCH") (62 . 7) (370 . 13) (100 . "AcDbLine") (10 19389.1402714932
5894.9067420814 0.0) (11 18676.4705882353 6199.0950226244 0.0))
((0 . "LINE") (100 . "AcDbEntity") (8 . "ARCH") (62 . 7) (370 . 13) (100 . "AcDbLine") (10 18676.4705882353
6199.0950226244 0.0) (11 17239.8190045249 6199.0950226244 0.0))
((0 . "LINE") (100 . "AcDbEntity") (8 . "ARCH") (62 . 7) (370 . 13) (100 . "AcDbLine") (10 19604.07239819
5803.1674208145 0.0) (11 19604.07239819 5757.9185520362 0.0))
((0 . "LINE") (100 . "AcDbEntity") (8 . "ARCH") (62 . 7) (370 . 13) (100 . "AcDbLine") (10 19604.07239819
5757.9185520362 0.0) (11 19581.4479638009 5746.6063348416 0.0))
((0 . "LINE") (100 . "AcDbEntity") (8 . "ARCH") (62 . 7) (370 . 13) (100 . "AcDbLine") (10 19581.4479638009
5746.6063348416 0.0) (11 19513.5746606335 5712.6696832579 0.0))
((0 . "LINE") (100 . "AcDbEntity") (8 . "ARCH") (62 . 7) (370 . 13) (100 . "AcDbLine") (10 19513.5746606335
5712.6696832579 0.0) (11 19513.5746606335 5667.4208144796 0.0))
((0 . "LINE") (100 . "AcDbEntity") (8 . "ARCH") (62 . 7) (370 . 13) (100 . "AcDbLine") (10 19513.5746606335
5667.4208144796 0.0) (11 19468.3257918552 5667.4208144796 0.0))
((0 . "LINE") (100 . "AcDbEntity") (8 . "ARCH") (62 . 7) (370 . 13) (100 . "AcDbLine") (10 19468.3257918552
5667.4208144796 0.0) (11 19468.3257918552 5599.5475113122 0.0))
((0 . "LINE") (100 . "AcDbEntity") (8 . "ARCH") (62 . 7) (370 . 13) (100 . "AcDbLine") (10 19468.3257918552
5599.5475113122 0.0) (11 19389.1402714932 5599.5475113122 0.0))
((0 . "LINE") (100 . "AcDbEntity") (8 . "ARCH") (62 . 7) (370 . 13) (100 . "AcDbLine") (10 19389.1402714932
5599.5475113122 0.0) (11 17239.8190045249 5599.5475113122 0.0))
((0 . "LINE") (100 . "AcDbEntity") (8 . "ARCH") (62 . 7) (370 . 13) (100 . "AcDbLine") (10 17239.8190045249
5803.1674208145 0.0) (11 19604.07239819 5803.1674208145 0.0))
((0 . "LINE") (100 . "AcDbEntity") (8 . "ARCH") (62 . 7) (370 . 13) (100 . "AcDbLine") (10 17239.8190045249
5746.6063348416 0.0) (11 19581.4479638009 5746.6063348416 0.0))
((0 . "LINE") (100 . "AcDbEntity") (8 . "ARCH") (62 . 7) (370 . 13) (100 . "AcDbLine") (10 17239.8190045249
5667.4208144796 0.0) (11 19468.3257918552 5667.4208144796 0.0))
((0 . "LINE") (100 . "AcDbEntity") (8 . "ARCH") (62 . 7) (370 . 13) (100 . "AcDbLine") (10 2782.8054298643
6481.9004524887 0.0) (11 2782.8054298643 6199.0950226244 0.0))
((0 . "LINE") (100 . "AcDbEntity") (8 . "ARCH") (62 . 7) (370 . 13) (100 . "AcDbLine") (10 2782.8054298643
6199.0950226244 0.0) (11 2782.8054298643 5814.4796380091 0.0))
((0 . "LINE") (100 . "AcDbEntity") (8 . "ARCH") (62 . 7) (370 . 13) (100 . "AcDbLine") (10 2782.8054298643
5814.4796380091 0.0) (11 2782.8054298643 5803.1674208145 0.0))
((0 . "LINE") (100 . "AcDbEntity") (8 . "ARCH") (62 . 7) (370 . 13) (100 . "AcDbLine") (10 2782.8054298643
5803.1674208145 0.0) (11 2782.8054298643 5746.6063348416 0.0))
((0 . "LINE") (100 . "AcDbEntity") (8 . "ARCH") (62 . 7) (370 . 13) (100 . "AcDbLine") (10 2782.8054298643
5746.6063348416 0.0) (11 2782.8054298643 5667.4208144796 0.0))
((0 . "LINE") (100 . "AcDbEntity") (8 . "ARCH") (62 . 7) (370 . 13) (100 . "AcDbLine") (10 2782.8054298643
5667.4208144796 0.0) (11 2782.8054298643 5622.1719457014 0.0))
((0 . "LINE") (100 . "AcDbEntity") (8 . "ARCH") (62 . 7) (370 . 13) (100 . "AcDbLine") (10 7929.8642533937
6481.9004524887 0.0) (11 7929.8642533937 6470.5882352941 0.0))
((0 . "LINE") (100 . "AcDbEntity") (8 . "ARCH") (62 . 7) (370 . 13) (100 . "AcDbLine") (10 7929.8642533937
6470.5882352941 0.0) (11 7929.8642533937 6199.0950226244 0.0))
((0 . "LINE") (100 . "AcDbEntity") (8 . "ARCH") (62 . 7) (370 . 13) (100 . "AcDbLine") (10 7929.8642533937
6199.0950226244 0.0) (11 7929.8642533937 5814.4796380091 0.0))
((0 . "LINE") (100 . "AcDbEntity") (8 . "ARCH") (62 . 7) (370 . 13) (100 . "AcDbLine") (10 7929.8642533937
5814.4796380091 0.0) (11 7929.8642533937 5746.6063348416 0.0))
((0 . "LINE") (100 . "AcDbEntity") (8 . "ARCH") (62 . 7) (370 . 13) (100 . "AcDbLine") (10 7929.8642533937
5746.6063348416 0.0) (11 7929.8642533937 5735.2941176471 0.0))
((0 . "LINE") (100 . "AcDbEntity") (8 . "ARCH") (62 . 7) (370 . 13) (100 . "AcDbLine") (10 7929.8642533937
5735.2941176471 0.0) (11 7929.8642533937 5610.8597285068 0.0))
((0 . "LINE") (100 . "AcDbEntity") (8 . "ARCH") (62 . 7) (370 . 13) (100 . "AcDbLine") (10 7929.8642533937
5610.8597285068 0.0) (11 7929.8642533937 5599.5475113122 0.0))
((0 . "LINE") (100 . "AcDbEntity") (8 . "ARCH") (62 . 7) (370 . 13) (100 . "AcDbLine") (10 7929.8642533937
5599.5475113122 0.0) (11 7929.8642533937 4909.5022624434 0.0))
((0 . "LINE") (100 . "AcDbEntity") (8 . "ARCH") (62 . 7) (370 . 13) (100 . "AcDbLine") (10 7929.8642533937
4909.5022624434 0.0) (11 7929.8642533937 3789.592760181 0.0))
((0 . "LINE") (100 . "AcDbEntity") (8 . "ARCH") (62 . 7) (370 . 13) (100 . "AcDbLine") (10 2782.8054298643
3597.2850678733 0.0) (11 2782.8054298643 3585.9728506787 0.0))
((0 . "LINE") (100 . "AcDbEntity") (8 . "ARCH") (62 . 7) (370 . 13) (100 . "AcDbLine") (10 2782.8054298643
3585.9728506787 0.0) (11 2782.8054298643 2997.7375565611 0.0))
((0 . "LINE") (100 . "AcDbEntity") (8 . "ARCH") (62 . 7) (370 . 13) (100 . "AcDbLine") (10 7929.8642533937
3597.2850678733 0.0) (11 7929.8642533937 3585.9728506787 0.0))
((0 . "LINE") (100 . "AcDbEntity") (8 . "ARCH") (62 . 7) (370 . 13) (100 . "AcDbLine") (10 7929.8642533937
3585.9728506787 0.0) (11 7929.8642533937 2816.742081448 0.0))
((0 . "LINE") (100 . "AcDbEntity") (8 . "ARCH") (62 . 7) (370 . 13) (100 . "AcDbLine") (10 7929.8642533937
2816.742081448 0.0) (11 7929.8642533937 2703.6199095023 0.0))
((0 . "LINE") (100 . "AcDbEntity") (8 . "ARCH") (62 . 7) (370 . 13) (100 . "AcDbLine") (10 7929.8642533937
2703.6199095023 0.0) (11 7929.8642533937 158.371040724 0.0))
((0 . "LINE") (100 . "AcDbEntity") (8 . "ARCH") (62 . 7) (370 . 13) (100 . "AcDbLine") (10 7929.8642533937 158.371040724
0.0) (11 7929.8642533937 101.8099547511 0.0))
((0 . "LINE") (100 . "AcDbEntity") (8 . "ARCH") (62 . 7) (370 . 13) (100 . "AcDbLine") (10 7929.8642533937
101.8099547511 0.0) (11 7929.8642533937 45.2488687783 0.0))
((0 . "LINE") (100 . "AcDbEntity") (8 . "ARCH") (62 . 7) (370 . 13) (100 . "AcDbLine") (10 7929.8642533937 45.2488687783
0.0) (11 7929.8642533937 0.0 0.0))
((0 . "LINE") (100 . "AcDbEntity") (8 . "ARCH") (62 . 7) (370 . 13) (100 . "AcDbLine") (10 2726.2443438914
3789.592760181 0.0) (11 2782.8054298643 3789.592760181 0.0))
((0 . "LINE") (100 . "AcDbEntity") (8 . "ARCH") (62 . 7) (370 . 13) (100 . "AcDbLine") (10 2782.8054298643
3789.592760181 0.0) (11 7929.8642533937 3789.592760181 0.0))
((0 . "LINE") (100 . "AcDbEntity") (8 . "ARCH") (62 . 7) (370 . 13) (100 . "AcDbLine") (10 7929.8642533937
3789.592760181 0.0) (11 8020.3619909502 3789.592760181 0.0))
((0 . "LINE") (100 . "AcDbEntity") (8 . "ARCH") (62 . 7) (370 . 13) (100 . "AcDbLine") (10 8020.3619909502
3789.592760181 0.0) (11 8020.3619909502 3721.7194570136 0.0))
((0 . "LINE") (100 . "AcDbEntity") (8 . "ARCH") (62 . 7) (370 . 13) (100 . "AcDbLine") (10 8020.3619909502
3721.7194570136 0.0) (11 6787.3303167421 3721.7194570136 0.0))
((0 . "LINE") (100 . "AcDbEntity") (8 . "ARCH") (62 . 7) (370 . 13) (100 . "AcDbLine") (10 6787.3303167421
3721.7194570136 0.0) (11 4038.4615384615 3721.7194570136 0.0))
((0 . "LINE") (100 . "AcDbEntity") (8 . "ARCH") (62 . 7) (370 . 13) (100 . "AcDbLine") (10 4038.4615384615
3721.7194570136 0.0) (11 2726.2443438914 3721.7194570136 0.0))
((0 . "LINE") (100 . "AcDbEntity") (8 . "ARCH") (62 . 7) (370 . 13) (100 . "AcDbLine") (10 2726.2443438914
3721.7194570136 0.0) (11 2726.2443438914 3789.592760181 0.0))
((0 . "LINE") (100 . "AcDbEntity") (8 . "ARCH") (62 . 7) (370 . 13) (100 . "AcDbLine") (10 2726.2443438914
3721.7194570136 0.0) (11 2771.4932126697 3642.5339366516 0.0))
((0 . "LINE") (100 . "AcDbEntity") (8 . "ARCH") (62 . 7) (370 . 13) (100 . "AcDbLine") (10 2771.4932126697
3642.5339366516 0.0) (11 2771.4932126697 3585.9728506787 0.0))
((0 . "LINE") (100 . "AcDbEntity") (8 . "ARCH") (62 . 7) (370 . 13) (100 . "AcDbLine") (10 2771.4932126697
3585.9728506787 0.0) (11 2782.8054298643 3585.9728506787 0.0))
((0 . "LINE") (100 . "AcDbEntity") (8 . "ARCH") (62 . 7) (370 . 13) (100 . "AcDbLine") (10 2782.8054298643
3585.9728506787 0.0) (11 4038.4615384615 3585.9728506787 0.0))
((0 . "LINE") (100 . "AcDbEntity") (8 . "ARCH") (62 . 7) (370 . 13) (100 . "AcDbLine") (10 4038.4615384615
3585.9728506787 0.0) (11 6787.3303167421 3585.9728506787 0.0))
((0 . "LINE") (100 . "AcDbEntity") (8 . "ARCH") (62 . 7) (370 . 13) (100 . "AcDbLine") (10 6787.3303167421
3585.9728506787 0.0) (11 7929.8642533937 3585.9728506787 0.0))
((0 . "LINE") (100 . "AcDbEntity") (8 . "ARCH") (62 . 7) (370 . 13) (100 . "AcDbLine") (10 7929.8642533937
3585.9728506787 0.0) (11 7963.8009049774 3585.9728506787 0.0))
((0 . "LINE") (100 . "AcDbEntity") (8 . "ARCH") (62 . 7) (370 . 13) (100 . "AcDbLine") (10 7963.8009049774
3585.9728506787 0.0) (11 7963.8009049774 3642.5339366516 0.0))
((0 . "LINE") (100 . "AcDbEntity") (8 . "ARCH") (62 . 7) (370 . 13) (100 . "AcDbLine") (10 7963.8009049774
3642.5339366516 0.0) (11 8020.3619909502 3721.7194570136 0.0))
((0 . "LINE") (100 . "AcDbEntity") (8 . "ARCH") (62 . 7) (370 . 13) (100 . "AcDbLine") (10 2782.8054298643
5814.4796380091 0.0) (11 4004.5248868778 5814.4796380091 0.0))
((0 . "LINE") (100 . "AcDbEntity") (8 . "ARCH") (62 . 7) (370 . 13) (100 . "AcDbLine") (10 6843.8914027149
5814.4796380091 0.0) (11 7929.8642533937 5814.4796380091 0.0))
((0 . "LINE") (100 . "AcDbEntity") (8 . "ARCH") (62 . 7) (370 . 13) (100 . "AcDbLine") (10 2782.8054298643
5746.6063348416 0.0) (11 4038.4615384615 5746.6063348416 0.0))
((0 . "LINE") (100 . "AcDbEntity") (8 . "ARCH") (62 . 7) (370 . 13) (100 . "AcDbLine") (10 6787.3303167421
5746.6063348416 0.0) (11 7929.8642533937 5746.6063348416 0.0))
((0 . "LINE") (100 . "AcDbEntity") (8 . "ARCH") (62 . 7) (370 . 13) (100 . "AcDbLine") (10 2782.8054298643
5610.8597285068 0.0) (11 3235.2941176471 5610.8597285068 0.0))
((0 . "LINE") (100 . "AcDbEntity") (8 . "ARCH") (62 . 7) (370 . 13) (100 . "AcDbLine") (10 3235.2941176471
5610.8597285068 0.0) (11 3285.8031674208 5610.8597285068 0.0))
((0 . "LINE") (100 . "AcDbEntity") (8 . "ARCH") (62 . 7) (370 . 13) (100 . "AcDbLine") (10 3285.8031674208
5610.8597285068 0.0) (11 3315.9615384615 5610.8597285068 0.0))
((0 . "LINE") (100 . "AcDbEntity") (8 . "ARCH") (62 . 7) (370 . 13) (100 . "AcDbLine") (10 3315.9615384615
5610.8597285068 0.0) (11 3362.0814479638 5610.8597285068 0.0))
((0 . "LINE") (100 . "AcDbEntity") (8 . "ARCH") (62 . 7) (370 . 13) (100 . "AcDbLine") (10 3362.0814479638
5610.8597285068 0.0) (11 3390.8823529412 5610.8597285068 0.0))
((0 . "LINE") (100 . "AcDbEntity") (8 . "ARCH") (62 . 7) (370 . 13) (100 . "AcDbLine") (10 3390.8823529412
5610.8597285068 0.0) (11 3440.7126696833 5610.8597285068 0.0))
((0 . "LINE") (100 . "AcDbEntity") (8 . "ARCH") (62 . 7) (370 . 13) (100 . "AcDbLine") (10 3440.7126696833
5610.8597285068 0.0) (11 3507.0701357466 5610.8597285068 0.0))
((0 . "LINE") (100 . "AcDbEntity") (8 . "ARCH") (62 . 7) (370 . 13) (100 . "AcDbLine") (10 3507.0701357466
5610.8597285068 0.0) (11 3526.1538461538 5610.8597285068 0.0))
((0 . "LINE") (100 . "AcDbEntity") (8 . "ARCH") (62 . 7) (370 . 13) (100 . "AcDbLine") (10 3526.1538461538
5610.8597285068 0.0) (11 3573.5520361991 5610.8597285068 0.0))
((0 . "LINE") (100 . "AcDbEntity") (8 . "ARCH") (62 . 7) (370 . 13) (100 . "AcDbLine") (10 3573.5520361991
5610.8597285068 0.0) (11 3643.2352941176 5610.8597285068 0.0))
((0 . "LINE") (100 . "AcDbEntity") (8 . "ARCH") (62 . 7) (370 . 13) (100 . "AcDbLine") (10 3643.2352941176
5610.8597285068 0.0) (11 3663.9819004525 5610.8597285068 0.0))
((0 . "LINE") (100 . "AcDbEntity") (8 . "ARCH") (62 . 7) (370 . 13) (100 . "AcDbLine") (10 3663.9819004525
5610.8597285068 0.0) (11 3712.1380090498 5610.8597285068 0.0))
((0 . "LINE") (100 . "AcDbEntity") (8 . "ARCH") (62 . 7) (370 . 13) (100 . "AcDbLine") (10 3712.1380090498
5610.8597285068 0.0) (11 3739.8076923077 5610.8597285068 0.0))
((0 . "LINE") (100 . "AcDbEntity") (8 . "ARCH") (62 . 7) (370 . 13) (100 . "AcDbLine") (10 3739.8076923077
5610.8597285068 0.0) (11 3791.4705882353 5610.8597285068 0.0))
((0 . "LINE") (100 . "AcDbEntity") (8 . "ARCH") (62 . 7) (370 . 13) (100 . "AcDbLine") (10 3791.4705882353
5610.8597285068 0.0) (11 3800.9049773756 5610.8597285068 0.0))
((0 . "LINE") (100 . "AcDbEntity") (8 . "ARCH") (62 . 7) (370 . 13) (100 . "AcDbLine") (10 3800.9049773756
5610.8597285068 0.0) (11 4162.8959276018 5610.8597285068 0.0))
((0 . "LINE") (100 . "AcDbEntity") (8 . "ARCH") (62 . 7) (370 . 13) (100 . "AcDbLine") (10 6708.1447963801
5610.8597285068 0.0) (11 7047.5113122172 5610.8597285068 0.0))
((0 . "LINE") (100 . "AcDbEntity") (8 . "ARCH") (62 . 7) (370 . 13) (100 . "AcDbLine") (10 7047.5113122172
5610.8597285068 0.0) (11 7096.7647058824 5610.8597285068 0.0))
((0 . "LINE") (100 . "AcDbEntity") (8 . "ARCH") (62 . 7) (370 . 13) (100 . "AcDbLine") (10 7096.7647058824
5610.8597285068 0.0) (11 7127.8959276018 5610.8597285068 0.0))
((0 . "LINE") (100 . "AcDbEntity") (8 . "ARCH") (62 . 7) (370 . 13) (100 . "AcDbLine") (10 7127.8959276018
5610.8597285068 0.0) (11 7172.2058823529 5610.8597285068 0.0))
((0 . "LINE") (100 . "AcDbEntity") (8 . "ARCH") (62 . 7) (370 . 13) (100 . "AcDbLine") (10 7172.2058823529
5610.8597285068 0.0) (11 7202.0701357466 5610.8597285068 0.0))
((0 . "LINE") (100 . "AcDbEntity") (8 . "ARCH") (62 . 7) (370 . 13) (100 . "AcDbLine") (10 7202.0701357466
5610.8597285068 0.0) (11 7246.0972850679 5610.8597285068 0.0))
((0 . "LINE") (100 . "AcDbEntity") (8 . "ARCH") (62 . 7) (370 . 13) (100 . "AcDbLine") (10 7246.0972850679
5610.8597285068 0.0) (11 7273.778280543 5610.8597285068 0.0))
((0 . "LINE") (100 . "AcDbEntity") (8 . "ARCH") (62 . 7) (370 . 13) (100 . "AcDbLine") (10 7273.778280543
5610.8597285068 0.0) (11 7322.4321266968 5610.8597285068 0.0))
((0 . "LINE") (100 . "AcDbEntity") (8 . "ARCH") (62 . 7) (370 . 13) (100 . "AcDbLine") (10 7322.4321266968
5610.8597285068 0.0) (11 7349.9321266968 5610.8597285068 0.0))
((0 . "LINE") (100 . "AcDbEntity") (8 . "ARCH") (62 . 7) (370 . 13) (100 . "AcDbLine") (10 7349.9321266968
5610.8597285068 0.0) (11 7393.7330316742 5610.8597285068 0.0))
((0 . "LINE") (100 . "AcDbEntity") (8 . "ARCH") (62 . 7) (370 . 13) (100 . "AcDbLine") (10 7393.7330316742
5610.8597285068 0.0) (11 7424.4909502262 5610.8597285068 0.0))
((0 . "LINE") (100 . "AcDbEntity") (8 . "ARCH") (62 . 7) (370 . 13) (100 . "AcDbLine") (10 7424.4909502262
5610.8597285068 0.0) (11 7463.6425339367 5610.8597285068 0.0))
((0 . "LINE") (100 . "AcDbEntity") (8 . "ARCH") (62 . 7) (370 . 13) (100 . "AcDbLine") (10 7463.6425339367
5610.8597285068 0.0) (11 7501.3800904977 5610.8597285068 0.0))
((0 . "LINE") (100 . "AcDbEntity") (8 . "ARCH") (62 . 7) (370 . 13) (100 . "AcDbLine") (10 7501.3800904977
5610.8597285068 0.0) (11 7529.7171945701 5610.8597285068 0.0))
((0 . "LINE") (100 . "AcDbEntity") (8 . "ARCH") (62 . 7) (370 . 13) (100 . "AcDbLine") (10 7529.7171945701
5610.8597285068 0.0) (11 7579.185520362 5610.8597285068 0.0))
((0 . "LINE") (100 . "AcDbEntity") (8 . "ARCH") (62 . 7) (370 . 13) (100 . "AcDbLine") (10 7579.185520362
5610.8597285068 0.0) (11 7929.8642533937 5610.8597285068 0.0))
((0 . "LINE") (100 . "AcDbEntity") (8 . "ARCH") (62 . 7) (370 . 13) (100 . "AcDbLine") (10 12036.1990950226
6481.9004524887 0.0) (11 12036.1990950226 6470.5882352941 0.0))
((0 . "LINE") (100 . "AcDbEntity") (8 . "ARCH") (62 . 7) (370 . 13) (100 . "AcDbLine") (10 12036.1990950226
6470.5882352941 0.0) (11 12036.1990950226 6199.0950226244 0.0))
((0 . "LINE") (100 . "AcDbEntity") (8 . "ARCH") (62 . 7) (370 . 13) (100 . "AcDbLine") (10 12036.1990950226
6199.0950226244 0.0) (11 12036.1990950226 5814.4796380091 0.0))
((0 . "LINE") (100 . "AcDbEntity") (8 . "ARCH") (62 . 7) (370 . 13) (100 . "AcDbLine") (10 12036.1990950226
5814.4796380091 0.0) (11 12036.1990950226 5746.6063348416 0.0))
((0 . "LINE") (100 . "AcDbEntity") (8 . "ARCH") (62 . 7) (370 . 13) (100 . "AcDbLine") (10 12036.1990950226
5746.6063348416 0.0) (11 12036.1990950226 5735.2941176471 0.0))
((0 . "LINE") (100 . "AcDbEntity") (8 . "ARCH") (62 . 7) (370 . 13) (100 . "AcDbLine") (10 12036.1990950226
5735.2941176471 0.0) (11 12036.1990950226 5610.8597285068 0.0))
((0 . "LINE") (100 . "AcDbEntity") (8 . "ARCH") (62 . 7) (370 . 13) (100 . "AcDbLine") (10 12036.1990950226
5610.8597285068 0.0) (11 12036.1990950226 5599.5475113122 0.0))
((0 . "LINE") (100 . "AcDbEntity") (8 . "ARCH") (62 . 7) (370 . 13) (100 . "AcDbLine") (10 12036.1990950226
5599.5475113122 0.0) (11 12036.1990950226 4909.5022624434 0.0))
((0 . "LINE") (100 . "AcDbEntity") (8 . "ARCH") (62 . 7) (370 . 13) (100 . "AcDbLine") (10 12036.1990950226
4909.5022624434 0.0) (11 12036.1990950226 3789.592760181 0.0))
((0 . "LINE") (100 . "AcDbEntity") (8 . "ARCH") (62 . 7) (370 . 13) (100 . "AcDbLine") (10 17239.8190045249
6481.9004524887 0.0) (11 17239.8190045249 6199.0950226244 0.0))
((0 . "LINE") (100 . "AcDbEntity") (8 . "ARCH") (62 . 7) (370 . 13) (100 . "AcDbLine") (10 17239.8190045249
6199.0950226244 0.0) (11 17239.8190045249 5814.4796380091 0.0))
((0 . "LINE") (100 . "AcDbEntity") (8 . "ARCH") (62 . 7) (370 . 13) (100 . "AcDbLine") (10 17239.8190045249
5814.4796380091 0.0) (11 17239.8190045249 5803.1674208145 0.0))
((0 . "LINE") (100 . "AcDbEntity") (8 . "ARCH") (62 . 7) (370 . 13) (100 . "AcDbLine") (10 17239.8190045249
5803.1674208145 0.0) (11 17239.8190045249 5746.6063348416 0.0))
((0 . "LINE") (100 . "AcDbEntity") (8 . "ARCH") (62 . 7) (370 . 13) (100 . "AcDbLine") (10 17239.8190045249
5746.6063348416 0.0) (11 17239.8190045249 5667.4208144796 0.0))
((0 . "LINE") (100 . "AcDbEntity") (8 . "ARCH") (62 . 7) (370 . 13) (100 . "AcDbLine") (10 17239.8190045249
5667.4208144796 0.0) (11 17239.8190045249 5622.1719457014 0.0))
((0 . "LINE") (100 . "AcDbEntity") (8 . "ARCH") (62 . 7) (370 . 13) (100 . "AcDbLine") (10 12036.1990950226
3597.2850678733 0.0) (11 12036.1990950226 3585.9728506787 0.0))
((0 . "LINE") (100 . "AcDbEntity") (8 . "ARCH") (62 . 7) (370 . 13) (100 . "AcDbLine") (10 12036.1990950226
3585.9728506787 0.0) (11 12036.1990950226 2816.742081448 0.0))
((0 . "LINE") (100 . "AcDbEntity") (8 . "ARCH") (62 . 7) (370 . 13) (100 . "AcDbLine") (10 12036.1990950226
2816.742081448 0.0) (11 12036.1990950226 2703.6199095023 0.0))
((0 . "LINE") (100 . "AcDbEntity") (8 . "ARCH") (62 . 7) (370 . 13) (100 . "AcDbLine") (10 12036.1990950226
2703.6199095023 0.0) (11 12036.1990950226 2070.525723721 0.0))
((0 . "LINE") (100 . "AcDbEntity") (8 . "ARCH") (62 . 7) (370 . 13) (100 . "AcDbLine") (10 12036.1990950226
2070.525723721 0.0) (11 12036.1990950226 192.3076923077 0.0))
((0 . "LINE") (100 . "AcDbEntity") (8 . "ARCH") (62 . 7) (370 . 13) (100 . "AcDbLine") (10 12036.1990950226
192.3076923077 0.0) (11 12036.1990950226 158.371040724 0.0))
((0 . "LINE") (100 . "AcDbEntity") (8 . "ARCH") (62 . 7) (370 . 13) (100 . "AcDbLine") (10 12036.1990950226
158.371040724 0.0) (11 12036.1990950226 101.8099547511 0.0))
((0 . "LINE") (100 . "AcDbEntity") (8 . "ARCH") (62 . 7) (370 . 13) (100 . "AcDbLine") (10 12036.1990950226
101.8099547511 0.0) (11 12036.1990950226 45.2488687783 0.0))
((0 . "LINE") (100 . "AcDbEntity") (8 . "ARCH") (62 . 7) (370 . 13) (100 . "AcDbLine") (10 12036.1990950226
45.2488687783 0.0) (11 12036.1990950226 0.0 0.0))
((0 . "LINE") (100 . "AcDbEntity") (8 . "ARCH") (62 . 7) (370 . 13) (100 . "AcDbLine") (10 17239.8190045249
2997.7375565611 0.0) (11 17239.8190045249 2861.9909502262 0.0))
((0 . "LINE") (100 . "AcDbEntity") (8 . "ARCH") (62 . 7) (370 . 13) (100 . "AcDbLine") (10 17239.8190045249
2861.9909502262 0.0) (11 17239.8190045249 2805.4298642534 0.0))
((0 . "LINE") (100 . "AcDbEntity") (8 . "ARCH") (62 . 7) (370 . 13) (100 . "AcDbLine") (10 11979.6380090498
3789.592760181 0.0) (11 12036.1990950226 3789.592760181 0.0))
((0 . "LINE") (100 . "AcDbEntity") (8 . "ARCH") (62 . 7) (370 . 13) (100 . "AcDbLine") (10 12036.1990950226
3789.592760181 0.0) (11 17239.8190045249 3789.592760181 0.0))
((0 . "LINE") (100 . "AcDbEntity") (8 . "ARCH") (62 . 7) (370 . 13) (100 . "AcDbLine") (10 17239.8190045249
3789.592760181 0.0) (11 17330.3167420814 3789.592760181 0.0))
((0 . "LINE") (100 . "AcDbEntity") (8 . "ARCH") (62 . 7) (370 . 13) (100 . "AcDbLine") (10 17330.3167420814
3789.592760181 0.0) (11 17330.3167420814 3721.7194570136 0.0))
((0 . "LINE") (100 . "AcDbEntity") (8 . "ARCH") (62 . 7) (370 . 13) (100 . "AcDbLine") (10 17330.3167420814
3721.7194570136 0.0) (11 17239.8190045249 3721.7194570136 0.0))
((0 . "LINE") (100 . "AcDbEntity") (8 . "ARCH") (62 . 7) (370 . 13) (100 . "AcDbLine") (10 17239.8190045249
3721.7194570136 0.0) (11 15938.9140271493 3721.7194570136 0.0))
((0 . "LINE") (100 . "AcDbEntity") (8 . "ARCH") (62 . 7) (370 . 13) (100 . "AcDbLine") (10 15938.9140271493
3721.7194570136 0.0) (11 13190.0452488688 3721.7194570136 0.0))
((0 . "LINE") (100 . "AcDbEntity") (8 . "ARCH") (62 . 7) (370 . 13) (100 . "AcDbLine") (10 13190.0452488688
3721.7194570136 0.0) (11 11979.6380090498 3721.7194570136 0.0))
((0 . "LINE") (100 . "AcDbEntity") (8 . "ARCH") (62 . 7) (370 . 13) (100 . "AcDbLine") (10 11979.6380090498
3721.7194570136 0.0) (11 11979.6380090498 3789.592760181 0.0))
((0 . "LINE") (100 . "AcDbEntity") (8 . "ARCH") (62 . 7) (370 . 13) (100 . "AcDbLine") (10 11979.6380090498
3721.7194570136 0.0) (11 12024.8868778281 3642.5339366516 0.0))
((0 . "LINE") (100 . "AcDbEntity") (8 . "ARCH") (62 . 7) (370 . 13) (100 . "AcDbLine") (10 12024.8868778281
3642.5339366516 0.0) (11 12024.8868778281 3585.9728506787 0.0))
((0 . "LINE") (100 . "AcDbEntity") (8 . "ARCH") (62 . 7) (370 . 13) (100 . "AcDbLine") (10 12024.8868778281
3585.9728506787 0.0) (11 12036.1990950226 3585.9728506787 0.0))
((0 . "LINE") (100 . "AcDbEntity") (8 . "ARCH") (62 . 7) (370 . 13) (100 . "AcDbLine") (10 12036.1990950226
3585.9728506787 0.0) (11 13190.0452488688 3585.9728506787 0.0))
((0 . "LINE") (100 . "AcDbEntity") (8 . "ARCH") (62 . 7) (370 . 13) (100 . "AcDbLine") (10 13190.0452488688
3585.9728506787 0.0) (11 15938.9140271493 3585.9728506787 0.0))
((0 . "LINE") (100 . "AcDbEntity") (8 . "ARCH") (62 . 7) (370 . 13) (100 . "AcDbLine") (10 15938.9140271493
3585.9728506787 0.0) (11 17239.8190045249 3585.9728506787 0.0))
((0 . "LINE") (100 . "AcDbEntity") (8 . "ARCH") (62 . 7) (370 . 13) (100 . "AcDbLine") (10 17239.8190045249
3585.9728506787 0.0) (11 17273.7556561086 3585.9728506787 0.0))
((0 . "LINE") (100 . "AcDbEntity") (8 . "ARCH") (62 . 7) (370 . 13) (100 . "AcDbLine") (10 17273.7556561086
3585.9728506787 0.0) (11 17273.7556561086 3642.5339366516 0.0))
((0 . "LINE") (100 . "AcDbEntity") (8 . "ARCH") (62 . 7) (370 . 13) (100 . "AcDbLine") (10 17273.7556561086
3642.5339366516 0.0) (11 17330.3167420814 3721.7194570136 0.0))
((0 . "LINE") (100 . "AcDbEntity") (8 . "ARCH") (62 . 7) (370 . 13) (100 . "AcDbLine") (10 12036.1990950226
5814.4796380091 0.0) (11 13156.1085972851 5814.4796380091 0.0))
((0 . "LINE") (100 . "AcDbEntity") (8 . "ARCH") (62 . 7) (370 . 13) (100 . "AcDbLine") (10 15995.4751131222
5814.4796380091 0.0) (11 17239.8190045249 5814.4796380091 0.0))
((0 . "LINE") (100 . "AcDbEntity") (8 . "ARCH") (62 . 7) (370 . 13) (100 . "AcDbLine") (10 12036.1990950226
5746.6063348416 0.0) (11 13190.0452488688 5746.6063348416 0.0))
((0 . "LINE") (100 . "AcDbEntity") (8 . "ARCH") (62 . 7) (370 . 13) (100 . "AcDbLine") (10 15938.9140271493
5746.6063348416 0.0) (11 17239.8190045249 5746.6063348416 0.0))
((0 . "LINE") (100 . "AcDbEntity") (8 . "ARCH") (62 . 7) (370 . 13) (100 . "AcDbLine") (10 12036.1990950226
5610.8597285068 0.0) (11 12420.814479638 5610.8597285068 0.0))
((0 . "LINE") (100 . "AcDbEntity") (8 . "ARCH") (62 . 7) (370 . 13) (100 . "AcDbLine") (10 12420.814479638
5610.8597285068 0.0) (11 12478.4162895928 5610.8597285068 0.0))
((0 . "LINE") (100 . "AcDbEntity") (8 . "ARCH") (62 . 7) (370 . 13) (100 . "AcDbLine") (10 12478.4162895928
5610.8597285068 0.0) (11 12505.7918552036 5610.8597285068 0.0))
((0 . "LINE") (100 . "AcDbEntity") (8 . "ARCH") (62 . 7) (370 . 13) (100 . "AcDbLine") (10 12505.7918552036
5610.8597285068 0.0) (11 12552.0022624434 5610.8597285068 0.0))
((0 . "LINE") (100 . "AcDbEntity") (8 . "ARCH") (62 . 7) (370 . 13) (100 . "AcDbLine") (10 12552.0022624434
5610.8597285068 0.0) (11 12642.3076923077 5610.8597285068 0.0))
((0 . "LINE") (100 . "AcDbEntity") (8 . "ARCH") (62 . 7) (370 . 13) (100 . "AcDbLine") (10 12642.3076923077
5610.8597285068 0.0) (11 12695.1583710407 5610.8597285068 0.0))
((0 . "LINE") (100 . "AcDbEntity") (8 . "ARCH") (62 . 7) (370 . 13) (100 . "AcDbLine") (10 12695.1583710407
5610.8597285068 0.0) (11 12711.742081448 5610.8597285068 0.0))
((0 . "LINE") (100 . "AcDbEntity") (8 . "ARCH") (62 . 7) (370 . 13) (100 . "AcDbLine") (10 12711.742081448
5610.8597285068 0.0) (11 12761.2556561086 5610.8597285068 0.0))
((0 . "LINE") (100 . "AcDbEntity") (8 . "ARCH") (62 . 7) (370 . 13) (100 . "AcDbLine") (10 12761.2556561086
5610.8597285068 0.0) (11 12790.3054298643 5610.8597285068 0.0))
((0 . "LINE") (100 . "AcDbEntity") (8 . "ARCH") (62 . 7) (370 . 13) (100 . "AcDbLine") (10 12790.3054298643
5610.8597285068 0.0) (11 12820.2941176471 5610.8597285068 0.0))
((0 . "LINE") (100 . "AcDbEntity") (8 . "ARCH") (62 . 7) (370 . 13) (100 . "AcDbLine") (10 12820.2941176471
5610.8597285068 0.0) (11 12864.592760181 5610.8597285068 0.0))
((0 . "LINE") (100 . "AcDbEntity") (8 . "ARCH") (62 . 7) (370 . 13) (100 . "AcDbLine") (10 12864.592760181
5610.8597285068 0.0) (11 12883.3936651584 5610.8597285068 0.0))
((0 . "LINE") (100 . "AcDbEntity") (8 . "ARCH") (62 . 7) (370 . 13) (100 . "AcDbLine") (10 12883.3936651584
5610.8597285068 0.0) (11 12940.6787330317 5610.8597285068 0.0))
((0 . "LINE") (100 . "AcDbEntity") (8 . "ARCH") (62 . 7) (370 . 13) (100 . "AcDbLine") (10 12940.6787330317
5610.8597285068 0.0) (11 12952.4886877828 5610.8597285068 0.0))
((0 . "LINE") (100 . "AcDbEntity") (8 . "ARCH") (62 . 7) (370 . 13) (100 . "AcDbLine") (10 12952.4886877828
5610.8597285068 0.0) (11 13314.4796380091 5610.8597285068 0.0))
((0 . "LINE") (100 . "AcDbEntity") (8 . "ARCH") (62 . 7) (370 . 13) (100 . "AcDbLine") (10 15859.7285067873
5610.8597285068 0.0) (11 16221.7194570136 5610.8597285068 0.0))
((0 . "LINE") (100 . "AcDbEntity") (8 . "ARCH") (62 . 7) (370 . 13) (100 . "AcDbLine") (10 16221.7194570136
5610.8597285068 0.0) (11 16274.2986425339 5610.8597285068 0.0))
((0 . "LINE") (100 . "AcDbEntity") (8 . "ARCH") (62 . 7) (370 . 13) (100 . "AcDbLine") (10 16274.2986425339
5610.8597285068 0.0) (11 16301.6063348416 5610.8597285068 0.0))
((0 . "LINE") (100 . "AcDbEntity") (8 . "ARCH") (62 . 7) (370 . 13) (100 . "AcDbLine") (10 16301.6063348416
5610.8597285068 0.0) (11 16348.3823529412 5610.8597285068 0.0))
((0 . "LINE") (100 . "AcDbEntity") (8 . "ARCH") (62 . 7) (370 . 13) (100 . "AcDbLine") (10 16348.3823529412
5610.8597285068 0.0) (11 16375.4524886878 5610.8597285068 0.0))
((0 . "LINE") (100 . "AcDbEntity") (8 . "ARCH") (62 . 7) (370 . 13) (100 . "AcDbLine") (10 16375.4524886878
5610.8597285068 0.0) (11 16442.3076923077 5610.8597285068 0.0))
((0 . "LINE") (100 . "AcDbEntity") (8 . "ARCH") (62 . 7) (370 . 13) (100 . "AcDbLine") (10 16442.3076923077
5610.8597285068 0.0) (11 16504.536199095 5610.8597285068 0.0))
((0 . "LINE") (100 . "AcDbEntity") (8 . "ARCH") (62 . 7) (370 . 13) (100 . "AcDbLine") (10 16504.536199095
5610.8597285068 0.0) (11 16540.9389140272 5610.8597285068 0.0))
((0 . "LINE") (100 . "AcDbEntity") (8 . "ARCH") (62 . 7) (370 . 13) (100 . "AcDbLine") (10 16540.9389140272
5610.8597285068 0.0) (11 16576.6742081448 5610.8597285068 0.0))
((0 . "LINE") (100 . "AcDbEntity") (8 . "ARCH") (62 . 7) (370 . 13) (100 . "AcDbLine") (10 16576.6742081448
5610.8597285068 0.0) (11 16625.5769230769 5610.8597285068 0.0))
((0 . "LINE") (100 . "AcDbEntity") (8 . "ARCH") (62 . 7) (370 . 13) (100 . "AcDbLine") (10 16625.5769230769
5610.8597285068 0.0) (11 16650.9389140271 5610.8597285068 0.0))
((0 . "LINE") (100 . "AcDbEntity") (8 . "ARCH") (62 . 7) (370 . 13) (100 . "AcDbLine") (10 16650.9389140271
5610.8597285068 0.0) (11 16696.1538461538 5610.8597285068 0.0))
((0 . "LINE") (100 . "AcDbEntity") (8 . "ARCH") (62 . 7) (370 . 13) (100 . "AcDbLine") (10 16696.1538461538
5610.8597285068 0.0) (11 16725.350678733 5610.8597285068 0.0))
((0 . "LINE") (100 . "AcDbEntity") (8 . "ARCH") (62 . 7) (370 . 13) (100 . "AcDbLine") (10 16725.350678733
5610.8597285068 0.0) (11 16773.7556561086 5610.8597285068 0.0))
((0 . "LINE") (100 . "AcDbEntity") (8 . "ARCH") (62 . 7) (370 . 13) (100 . "AcDbLine") (10 16773.7556561086
5610.8597285068 0.0) (11 16787.3303167421 5610.8597285068 0.0))
((0 . "LINE") (100 . "AcDbEntity") (8 . "ARCH") (62 . 7) (370 . 13) (100 . "AcDbLine") (10 16787.3303167421
5610.8597285068 0.0) (11 17239.8190045249 5610.8597285068 0.0))
((0 . "LINE") (100 . "AcDbEntity") (8 . "ARCH") (62 . 7) (370 . 13) (100 . "AcDbLine") (10 9547.5113122172
6425.3393665158 0.0) (11 10452.4886877828 6425.3393665158 0.0))
((0 . "LINE") (100 . "AcDbEntity") (8 . "ARCH") (62 . 7) (370 . 13) (100 . "AcDbLine") (10 10452.4886877828
6425.3393665158 0.0) (11 10452.4886877828 6199.0950226244 0.0))
((0 . "LINE") (100 . "AcDbEntity") (8 . "ARCH") (62 . 7) (370 . 13) (100 . "AcDbLine") (10 10452.4886877828
6199.0950226244 0.0) (11 10452.4886877828 5814.4796380091 0.0))
((0 . "LINE") (100 . "AcDbEntity") (8 . "ARCH") (62 . 7) (370 . 13) (100 . "AcDbLine") (10 10452.4886877828
5814.4796380091 0.0) (11 10452.4886877828 5735.2941176471 0.0))
((0 . "LINE") (100 . "AcDbEntity") (8 . "ARCH") (62 . 7) (370 . 13) (100 . "AcDbLine") (10 10452.4886877828
5735.2941176471 0.0) (11 10452.4886877828 5599.5475113122 0.0))
((0 . "LINE") (100 . "AcDbEntity") (8 . "ARCH") (62 . 7) (370 . 13) (100 . "AcDbLine") (10 10452.4886877828
5599.5475113122 0.0) (11 10452.4886877828 4909.5022624434 0.0))
((0 . "LINE") (100 . "AcDbEntity") (8 . "ARCH") (62 . 7) (370 . 13) (100 . "AcDbLine") (10 10452.4886877828
4909.5022624434 0.0) (11 10452.4886877828 2816.742081448 0.0))
((0 . "LINE") (100 . "AcDbEntity") (8 . "ARCH") (62 . 7) (370 . 13) (100 . "AcDbLine") (10 10452.4886877828
2816.742081448 0.0) (11 10452.4886877828 2703.6199095023 0.0))
((0 . "LINE") (100 . "AcDbEntity") (8 . "ARCH") (62 . 7) (370 . 13) (100 . "AcDbLine") (10 10452.4886877828
2703.6199095023 0.0) (11 10452.4886877828 158.371040724 0.0))
((0 . "LINE") (100 . "AcDbEntity") (8 . "ARCH") (62 . 7) (370 . 13) (100 . "AcDbLine") (10 10452.4886877828
158.371040724 0.0) (11 10452.4886877828 101.8099547511 0.0))
((0 . "LINE") (100 . "AcDbEntity") (8 . "ARCH") (62 . 7) (370 . 13) (100 . "AcDbLine") (10 10452.4886877828
101.8099547511 0.0) (11 10452.4886877828 45.2488687783 0.0))
((0 . "LINE") (100 . "AcDbEntity") (8 . "ARCH") (62 . 7) (370 . 13) (100 . "AcDbLine") (10 10452.4886877828
45.2488687783 0.0) (11 10452.4886877828 0.0 0.0))
((0 . "LINE") (100 . "AcDbEntity") (8 . "ARCH") (62 . 7) (370 . 13) (100 . "AcDbLine") (10 9547.5113122172 0.0 0.0) (11
9547.5113122172 45.2488687783 0.0))
((0 . "LINE") (100 . "AcDbEntity") (8 . "ARCH") (62 . 7) (370 . 13) (100 . "AcDbLine") (10 9547.5113122172 45.2488687783
0.0) (11 9547.5113122172 101.8099547511 0.0))
((0 . "LINE") (100 . "AcDbEntity") (8 . "ARCH") (62 . 7) (370 . 13) (100 . "AcDbLine") (10 9547.5113122172
101.8099547511 0.0) (11 9547.5113122172 158.371040724 0.0))
((0 . "LINE") (100 . "AcDbEntity") (8 . "ARCH") (62 . 7) (370 . 13) (100 . "AcDbLine") (10 9547.5113122172 158.371040724
0.0) (11 9547.5113122172 192.3076923077 0.0))
((0 . "LINE") (100 . "AcDbEntity") (8 . "ARCH") (62 . 7) (370 . 13) (100 . "AcDbLine") (10 9547.5113122172
192.3076923077 0.0) (11 9547.5113122172 2058.8235294118 0.0))
((0 . "LINE") (100 . "AcDbEntity") (8 . "ARCH") (62 . 7) (370 . 13) (100 . "AcDbLine") (10 9547.5113122172
2058.8235294118 0.0) (11 9547.5113122172 2703.6199095023 0.0))
((0 . "LINE") (100 . "AcDbEntity") (8 . "ARCH") (62 . 7) (370 . 13) (100 . "AcDbLine") (10 9547.5113122172
2703.6199095023 0.0) (11 9547.5113122172 2816.742081448 0.0))
((0 . "LINE") (100 . "AcDbEntity") (8 . "ARCH") (62 . 7) (370 . 13) (100 . "AcDbLine") (10 9547.5113122172
2816.742081448 0.0) (11 9547.5113122172 4909.5022624434 0.0))
((0 . "LINE") (100 . "AcDbEntity") (8 . "ARCH") (62 . 7) (370 . 13) (100 . "AcDbLine") (10 9547.5113122172
4909.5022624434 0.0) (11 9547.5113122172 5599.5475113122 0.0))
((0 . "LINE") (100 . "AcDbEntity") (8 . "ARCH") (62 . 7) (370 . 13) (100 . "AcDbLine") (10 9547.5113122172
5599.5475113122 0.0) (11 9547.5113122172 5735.2941176471 0.0))
((0 . "LINE") (100 . "AcDbEntity") (8 . "ARCH") (62 . 7) (370 . 13) (100 . "AcDbLine") (10 9547.5113122172
5735.2941176471 0.0) (11 9547.5113122172 5814.4796380091 0.0))
((0 . "LINE") (100 . "AcDbEntity") (8 . "ARCH") (62 . 7) (370 . 13) (100 . "AcDbLine") (10 9547.5113122172
5814.4796380091 0.0) (11 9547.5113122172 6199.0950226244 0.0))
((0 . "LINE") (100 . "AcDbEntity") (8 . "ARCH") (62 . 7) (370 . 13) (100 . "AcDbLine") (10 9547.5113122172
6199.0950226244 0.0) (11 9547.5113122172 6425.3393665158 0.0))
((0 . "LINE") (100 . "AcDbEntity") (8 . "ARCH") (62 . 7) (370 . 13) (100 . "AcDbLine") (10 9377.8280542986
6809.9547511312 0.0) (11 9649.3212669683 6809.9547511312 0.0))
((0 . "LINE") (100 . "AcDbEntity") (8 . "ARCH") (62 . 7) (370 . 13) (100 . "AcDbLine") (10 9649.3212669683
6809.9547511312 0.0) (11 9751.1312217195 6809.9547511312 0.0))
((0 . "LINE") (100 . "AcDbEntity") (8 . "ARCH") (62 . 7) (370 . 13) (100 . "AcDbLine") (10 9751.1312217195
6809.9547511312 0.0) (11 9807.6923076923 6809.9547511312 0.0))
((0 . "LINE") (100 . "AcDbEntity") (8 . "ARCH") (62 . 7) (370 . 13) (100 . "AcDbLine") (10 9807.6923076923
6809.9547511312 0.0) (11 10316.742081448 6809.9547511312 0.0))
((0 . "LINE") (100 . "AcDbEntity") (8 . "ARCH") (62 . 7) (370 . 13) (100 . "AcDbLine") (10 10316.742081448
6809.9547511312 0.0) (11 10373.3031674208 6809.9547511312 0.0))
((0 . "LINE") (100 . "AcDbEntity") (8 . "ARCH") (62 . 7) (370 . 13) (100 . "AcDbLine") (10 10373.3031674208
6809.9547511312 0.0) (11 10475.1131221719 6809.9547511312 0.0))
((0 . "LINE") (100 . "AcDbEntity") (8 . "ARCH") (62 . 7) (370 . 13) (100 . "AcDbLine") (10 10475.1131221719
6809.9547511312 0.0) (11 10633.4841628959 6809.9547511312 0.0))
((0 . "LINE") (100 . "AcDbEntity") (8 . "ARCH") (62 . 7) (370 . 13) (100 . "AcDbLine") (10 10633.4841628959
6809.9547511312 0.0) (11 10633.4841628959 6761.8212669683 0.0))
((0 . "LINE") (100 . "AcDbEntity") (8 . "ARCH") (62 . 7) (370 . 13) (100 . "AcDbLine") (10 10633.4841628959
6761.8212669683 0.0) (11 10633.4841628959 6730.7692307692 0.0))
((0 . "LINE") (100 . "AcDbEntity") (8 . "ARCH") (62 . 7) (370 . 13) (100 . "AcDbLine") (10 10633.4841628959
6730.7692307692 0.0) (11 10619.3438914027 6719.4570135747 0.0))
((0 . "LINE") (100 . "AcDbEntity") (8 . "ARCH") (62 . 7) (370 . 13) (100 . "AcDbLine") (10 10619.3438914027
6719.4570135747 0.0) (11 10617.2087104072 6717.7488687783 0.0))
((0 . "LINE") (100 . "AcDbEntity") (8 . "ARCH") (62 . 7) (370 . 13) (100 . "AcDbLine") (10 10617.2087104072
6717.7488687783 0.0) (11 10579.9632352941 6687.9524886878 0.0))
((0 . "LINE") (100 . "AcDbEntity") (8 . "ARCH") (62 . 7) (370 . 13) (100 . "AcDbLine") (10 10579.9632352941
6687.9524886878 0.0) (11 10576.9230769231 6685.520361991 0.0))
((0 . "LINE") (100 . "AcDbEntity") (8 . "ARCH") (62 . 7) (370 . 13) (100 . "AcDbLine") (10 10576.9230769231
6685.520361991 0.0) (11 10541.556561086 6641.3122171946 0.0))
((0 . "LINE") (100 . "AcDbEntity") (8 . "ARCH") (62 . 7) (370 . 13) (100 . "AcDbLine") (10 10541.556561086
6641.3122171946 0.0) (11 10540.7239819005 6640.2714932127 0.0))
((0 . "LINE") (100 . "AcDbEntity") (8 . "ARCH") (62 . 7) (370 . 13) (100 . "AcDbLine") (10 10540.7239819005
6640.2714932127 0.0) (11 10531.6742081448 6628.9592760181 0.0))
((0 . "LINE") (100 . "AcDbEntity") (8 . "ARCH") (62 . 7) (370 . 13) (100 . "AcDbLine") (10 10531.6742081448
6628.9592760181 0.0) (11 10531.6742081448 6607.0701357466 0.0))
((0 . "LINE") (100 . "AcDbEntity") (8 . "ARCH") (62 . 7) (370 . 13) (100 . "AcDbLine") (10 10531.6742081448
6607.0701357466 0.0) (11 10531.6742081448 6549.7737556561 0.0))
((0 . "LINE") (100 . "AcDbEntity") (8 . "ARCH") (62 . 7) (370 . 13) (100 . "AcDbLine") (10 10531.6742081448
6549.7737556561 0.0) (11 10531.6742081448 6470.5882352941 0.0))
((0 . "LINE") (100 . "AcDbEntity") (8 . "ARCH") (62 . 7) (370 . 13) (100 . "AcDbLine") (10 10531.6742081448
6470.5882352941 0.0) (11 10531.6742081448 6436.6515837104 0.0))
((0 . "LINE") (100 . "AcDbEntity") (8 . "ARCH") (62 . 7) (370 . 13) (100 . "AcDbLine") (10 10531.6742081448
6436.6515837104 0.0) (11 9479.6380090498 6436.6515837104 0.0))
((0 . "LINE") (100 . "AcDbEntity") (8 . "ARCH") (62 . 7) (370 . 13) (100 . "AcDbLine") (10 9479.6380090498
6436.6515837104 0.0) (11 9479.6380090498 6470.5882352941 0.0))
((0 . "LINE") (100 . "AcDbEntity") (8 . "ARCH") (62 . 7) (370 . 13) (100 . "AcDbLine") (10 9479.6380090498
6470.5882352941 0.0) (11 9479.6380090498 6549.7737556561 0.0))
((0 . "LINE") (100 . "AcDbEntity") (8 . "ARCH") (62 . 7) (370 . 13) (100 . "AcDbLine") (10 9479.6380090498
6549.7737556561 0.0) (11 9479.6380090498 6607.2624434389 0.0))
((0 . "LINE") (100 . "AcDbEntity") (8 . "ARCH") (62 . 7) (370 . 13) (100 . "AcDbLine") (10 9479.6380090498
6607.2624434389 0.0) (11 9479.6380090498 6628.9592760181 0.0))
((0 . "LINE") (100 . "AcDbEntity") (8 . "ARCH") (62 . 7) (370 . 13) (100 . "AcDbLine") (10 9479.6380090498
6628.9592760181 0.0) (11 9470.5882352941 6640.2714932127 0.0))
((0 . "LINE") (100 . "AcDbEntity") (8 . "ARCH") (62 . 7) (370 . 13) (100 . "AcDbLine") (10 9470.5882352941
6640.2714932127 0.0) (11 9468.3257918552 6643.0995475113 0.0))
((0 . "LINE") (100 . "AcDbEntity") (8 . "ARCH") (62 . 7) (370 . 13) (100 . "AcDbLine") (10 9468.3257918552
6643.0995475113 0.0) (11 9434.3891402715 6685.520361991 0.0))
((0 . "LINE") (100 . "AcDbEntity") (8 . "ARCH") (62 . 7) (370 . 13) (100 . "AcDbLine") (10 9434.3891402715
6685.520361991 0.0) (11 9402.9411764706 6710.6787330317 0.0))
((0 . "LINE") (100 . "AcDbEntity") (8 . "ARCH") (62 . 7) (370 . 13) (100 . "AcDbLine") (10 9402.9411764706
6710.6787330317 0.0) (11 9391.9683257919 6719.4570135747 0.0))
((0 . "LINE") (100 . "AcDbEntity") (8 . "ARCH") (62 . 7) (370 . 13) (100 . "AcDbLine") (10 9391.9683257919
6719.4570135747 0.0) (11 9377.8280542986 6730.7692307692 0.0))
((0 . "LINE") (100 . "AcDbEntity") (8 . "ARCH") (62 . 7) (370 . 13) (100 . "AcDbLine") (10 9377.8280542986
6730.7692307692 0.0) (11 9377.8280542986 6762.4547511312 0.0))
((0 . "LINE") (100 . "AcDbEntity") (8 . "ARCH") (62 . 7) (370 . 13) (100 . "AcDbLine") (10 9377.8280542986
6762.4547511312 0.0) (11 9377.8280542986 6809.9547511312 0.0))
((0 . "LINE") (100 . "AcDbEntity") (8 . "ARCH") (62 . 7) (370 . 13) (100 . "AcDbLine") (10 9389.1402714932
6719.4570135747 0.0) (11 9391.9683257919 6719.4570135747 0.0))
((0 . "LINE") (100 . "AcDbEntity") (8 . "ARCH") (62 . 7) (370 . 13) (100 . "AcDbLine") (10 9391.9683257919
6719.4570135747 0.0) (11 10619.3438914027 6719.4570135747 0.0))
((0 . "LINE") (100 . "AcDbEntity") (8 . "ARCH") (62 . 7) (370 . 13) (100 . "AcDbLine") (10 10619.3438914027
6719.4570135747 0.0) (11 10622.1719457014 6719.4570135747 0.0))
((0 . "LINE") (100 . "AcDbEntity") (8 . "ARCH") (62 . 7) (370 . 13) (100 . "AcDbLine") (10 9468.3257918552
6640.2714932127 0.0) (11 9470.5882352941 6640.2714932127 0.0))
((0 . "LINE") (100 . "AcDbEntity") (8 . "ARCH") (62 . 7) (370 . 13) (100 . "AcDbLine") (10 9470.5882352941
6640.2714932127 0.0) (11 10540.7239819005 6640.2714932127 0.0))
((0 . "LINE") (100 . "AcDbEntity") (8 . "ARCH") (62 . 7) (370 . 13) (100 . "AcDbLine") (10 10540.7239819005
6640.2714932127 0.0) (11 10542.9864253394 6640.2714932127 0.0))
((0 . "LINE") (100 . "AcDbEntity") (8 . "ARCH") (62 . 7) (370 . 13) (100 . "AcDbLine") (10 7929.8642533937
6199.0950226244 0.0) (11 9547.5113122172 6199.0950226244 0.0))
((0 . "LINE") (100 . "AcDbEntity") (8 . "ARCH") (62 . 7) (370 . 13) (100 . "AcDbLine") (10 7929.8642533937
5814.4796380091 0.0) (11 9547.5113122172 5814.4796380091 0.0))
((0 . "LINE") (100 . "AcDbEntity") (8 . "ARCH") (62 . 7) (370 . 13) (100 . "AcDbLine") (10 7929.8642533937
5735.2941176471 0.0) (11 9547.5113122172 5735.2941176471 0.0))
((0 . "LINE") (100 . "AcDbEntity") (8 . "ARCH") (62 . 7) (370 . 13) (100 . "AcDbLine") (10 7929.8642533937
5599.5475113122 0.0) (11 9547.5113122172 5599.5475113122 0.0))
((0 . "LINE") (100 . "AcDbEntity") (8 . "ARCH") (62 . 7) (370 . 13) (100 . "AcDbLine") (10 7929.8642533937
2816.742081448 0.0) (11 9547.5113122172 2816.742081448 0.0))
((0 . "LINE") (100 . "AcDbEntity") (8 . "ARCH") (62 . 7) (370 . 13) (100 . "AcDbLine") (10 7929.8642533937
2703.6199095023 0.0) (11 9547.5113122172 2703.6199095023 0.0))
((0 . "LINE") (100 . "AcDbEntity") (8 . "ARCH") (62 . 7) (370 . 13) (100 . "AcDbLine") (10 7929.8642533937
4909.5022624434 0.0) (11 8212.6696832579 4909.5022624434 0.0))
((0 . "LINE") (100 . "AcDbEntity") (8 . "ARCH") (62 . 7) (370 . 13) (100 . "AcDbLine") (10 9298.6425339367
4909.5022624434 0.0) (11 9547.5113122172 4909.5022624434 0.0))
((0 . "LINE") (100 . "AcDbEntity") (8 . "ARCH") (62 . 7) (370 . 13) (100 . "AcDbLine") (10 10452.4886877828
6199.0950226244 0.0) (11 12036.1990950226 6199.0950226244 0.0))
((0 . "LINE") (100 . "AcDbEntity") (8 . "ARCH") (62 . 7) (370 . 13) (100 . "AcDbLine") (10 10452.4886877828
5814.4796380091 0.0) (11 12036.1990950226 5814.4796380091 0.0))
((0 . "LINE") (100 . "AcDbEntity") (8 . "ARCH") (62 . 7) (370 . 13) (100 . "AcDbLine") (10 10452.4886877828
5735.2941176471 0.0) (11 12036.1990950226 5735.2941176471 0.0))
((0 . "LINE") (100 . "AcDbEntity") (8 . "ARCH") (62 . 7) (370 . 13) (100 . "AcDbLine") (10 10452.4886877828
5599.5475113122 0.0) (11 12036.1990950226 5599.5475113122 0.0))
((0 . "LINE") (100 . "AcDbEntity") (8 . "ARCH") (62 . 7) (370 . 13) (100 . "AcDbLine") (10 10452.4886877828
2816.742081448 0.0) (11 12036.1990950226 2816.742081448 0.0))
((0 . "LINE") (100 . "AcDbEntity") (8 . "ARCH") (62 . 7) (370 . 13) (100 . "AcDbLine") (10 10452.4886877828
2703.6199095023 0.0) (11 12036.1990950226 2703.6199095023 0.0))
((0 . "LINE") (100 . "AcDbEntity") (8 . "ARCH") (62 . 7) (370 . 13) (100 . "AcDbLine") (10 10452.4886877828
4909.5022624434 0.0) (11 10712.6696832579 4909.5022624434 0.0))
((0 . "LINE") (100 . "AcDbEntity") (8 . "ARCH") (62 . 7) (370 . 13) (100 . "AcDbLine") (10 11798.6425339367
4909.5022624434 0.0) (11 12036.1990950226 4909.5022624434 0.0))
((0 . "LINE") (100 . "AcDbEntity") (8 . "ARCH") (62 . 7) (370 . 13) (100 . "AcDbLine") (10 7952.4886877828
6549.7737556561 0.0) (11 8009.0497737557 6549.7737556561 0.0))
((0 . "LINE") (100 . "AcDbEntity") (8 . "ARCH") (62 . 7) (370 . 13) (100 . "AcDbLine") (10 8009.0497737557
6549.7737556561 0.0) (11 8597.2850678733 6549.7737556561 0.0))
((0 . "LINE") (100 . "AcDbEntity") (8 . "ARCH") (62 . 7) (370 . 13) (100 . "AcDbLine") (10 8597.2850678733
6549.7737556561 0.0) (11 8597.2850678733 6391.4027149321 0.0))
((0 . "LINE") (100 . "AcDbEntity") (8 . "ARCH") (62 . 7) (370 . 13) (100 . "AcDbLine") (10 8597.2850678733
6391.4027149321 0.0) (11 8766.9683257919 6391.4027149321 0.0))
((0 . "LINE") (100 . "AcDbEntity") (8 . "ARCH") (62 . 7) (370 . 13) (100 . "AcDbLine") (10 8766.9683257919
6391.4027149321 0.0) (11 8766.9683257919 6549.7737556561 0.0))
((0 . "LINE") (100 . "AcDbEntity") (8 . "ARCH") (62 . 7) (370 . 13) (100 . "AcDbLine") (10 8766.9683257919
6549.7737556561 0.0) (11 8947.963800905 6549.7737556561 0.0))
((0 . "LINE") (100 . "AcDbEntity") (8 . "ARCH") (62 . 7) (370 . 13) (100 . "AcDbLine") (10 8947.963800905
6549.7737556561 0.0) (11 9004.5248868778 6549.7737556561 0.0))
((0 . "LINE") (100 . "AcDbEntity") (8 . "ARCH") (62 . 7) (370 . 13) (100 . "AcDbLine") (10 9004.5248868778
6549.7737556561 0.0) (11 9106.334841629 6549.7737556561 0.0))
((0 . "LINE") (100 . "AcDbEntity") (8 . "ARCH") (62 . 7) (370 . 13) (100 . "AcDbLine") (10 9106.334841629
6549.7737556561 0.0) (11 9479.6380090498 6549.7737556561 0.0))
((0 . "LINE") (100 . "AcDbEntity") (8 . "ARCH") (62 . 7) (370 . 13) (100 . "AcDbLine") (10 7929.8642533937
6470.5882352941 0.0) (11 8529.4117647059 6470.5882352941 0.0))
((0 . "LINE") (100 . "AcDbEntity") (8 . "ARCH") (62 . 7) (370 . 13) (100 . "AcDbLine") (10 8529.4117647059
6470.5882352941 0.0) (11 8529.4117647059 6334.8416289593 0.0))
((0 . "LINE") (100 . "AcDbEntity") (8 . "ARCH") (62 . 7) (370 . 13) (100 . "AcDbLine") (10 8529.4117647059
6334.8416289593 0.0) (11 8834.8416289593 6334.8416289593 0.0))
((0 . "LINE") (100 . "AcDbEntity") (8 . "ARCH") (62 . 7) (370 . 13) (100 . "AcDbLine") (10 8834.8416289593
6334.8416289593 0.0) (11 8834.8416289593 6470.5882352941 0.0))
((0 . "LINE") (100 . "AcDbEntity") (8 . "ARCH") (62 . 7) (370 . 13) (100 . "AcDbLine") (10 8834.8416289593
6470.5882352941 0.0) (11 9479.6380090498 6470.5882352941 0.0))
((0 . "LINE") (100 . "AcDbEntity") (8 . "ARCH") (62 . 7) (370 . 13) (100 . "AcDbLine") (10 10531.6742081448
6549.7737556561 0.0) (11 10927.6018099548 6549.7737556561 0.0))
((0 . "LINE") (100 . "AcDbEntity") (8 . "ARCH") (62 . 7) (370 . 13) (100 . "AcDbLine") (10 10927.6018099548
6549.7737556561 0.0) (11 11029.4117647059 6549.7737556561 0.0))
((0 . "LINE") (100 . "AcDbEntity") (8 . "ARCH") (62 . 7) (370 . 13) (100 . "AcDbLine") (10 11029.4117647059
6549.7737556561 0.0) (11 11085.9728506787 6549.7737556561 0.0))
((0 . "LINE") (100 . "AcDbEntity") (8 . "ARCH") (62 . 7) (370 . 13) (100 . "AcDbLine") (10 11085.9728506787
6549.7737556561 0.0) (11 11142.5339366516 6549.7737556561 0.0))
((0 . "LINE") (100 . "AcDbEntity") (8 . "ARCH") (62 . 7) (370 . 13) (100 . "AcDbLine") (10 11142.5339366516
6549.7737556561 0.0) (11 11142.5339366516 6391.4027149321 0.0))
((0 . "LINE") (100 . "AcDbEntity") (8 . "ARCH") (62 . 7) (370 . 13) (100 . "AcDbLine") (10 11142.5339366516
6391.4027149321 0.0) (11 11323.5294117647 6391.4027149321 0.0))
((0 . "LINE") (100 . "AcDbEntity") (8 . "ARCH") (62 . 7) (370 . 13) (100 . "AcDbLine") (10 11323.5294117647
6391.4027149321 0.0) (11 11323.5294117647 6549.7737556561 0.0))
((0 . "LINE") (100 . "AcDbEntity") (8 . "ARCH") (62 . 7) (370 . 13) (100 . "AcDbLine") (10 11323.5294117647
6549.7737556561 0.0) (11 11979.6380090498 6549.7737556561 0.0))
((0 . "LINE") (100 . "AcDbEntity") (8 . "ARCH") (62 . 7) (370 . 13) (100 . "AcDbLine") (10 11979.6380090498
6549.7737556561 0.0) (11 12036.1990950226 6549.7737556561 0.0))
((0 . "LINE") (100 . "AcDbEntity") (8 . "ARCH") (62 . 7) (370 . 13) (100 . "AcDbLine") (10 10531.6742081448
6470.5882352941 0.0) (11 11074.6606334842 6470.5882352941 0.0))
((0 . "LINE") (100 . "AcDbEntity") (8 . "ARCH") (62 . 7) (370 . 13) (100 . "AcDbLine") (10 11074.6606334842
6470.5882352941 0.0) (11 11074.6606334842 6334.8416289593 0.0))
((0 . "LINE") (100 . "AcDbEntity") (8 . "ARCH") (62 . 7) (370 . 13) (100 . "AcDbLine") (10 11074.6606334842
6334.8416289593 0.0) (11 11391.4027149321 6334.8416289593 0.0))
((0 . "LINE") (100 . "AcDbEntity") (8 . "ARCH") (62 . 7) (370 . 13) (100 . "AcDbLine") (10 11391.4027149321
6334.8416289593 0.0) (11 11391.4027149321 6470.5882352941 0.0))
((0 . "LINE") (100 . "AcDbEntity") (8 . "ARCH") (62 . 7) (370 . 13) (100 . "AcDbLine") (10 11391.4027149321
6470.5882352941 0.0) (11 12036.1990950226 6470.5882352941 0.0))
((0 . "LINE") (100 . "AcDbEntity") (8 . "ARCH") (62 . 7) (370 . 13) (100 . "AcDbLine") (10 4276.0180995475
6549.7737556561 0.0) (11 4309.9547511312 6549.7737556561 0.0))
((0 . "LINE") (100 . "AcDbEntity") (8 . "ARCH") (62 . 7) (370 . 13) (100 . "AcDbLine") (10 4309.9547511312
6549.7737556561 0.0) (11 4434.3891402715 6549.7737556561 0.0))
((0 . "LINE") (100 . "AcDbEntity") (8 . "ARCH") (62 . 7) (370 . 13) (100 . "AcDbLine") (10 4434.3891402715
6549.7737556561 0.0) (11 4490.9502262443 6549.7737556561 0.0))
((0 . "LINE") (100 . "AcDbEntity") (8 . "ARCH") (62 . 7) (370 . 13) (100 . "AcDbLine") (10 4490.9502262443
6549.7737556561 0.0) (11 6572.3981900452 6549.7737556561 0.0))
((0 . "LINE") (100 . "AcDbEntity") (8 . "ARCH") (62 . 7) (370 . 13) (100 . "AcDbLine") (10 6572.3981900452
6549.7737556561 0.0) (11 6628.9592760181 6549.7737556561 0.0))
((0 . "LINE") (100 . "AcDbEntity") (8 . "ARCH") (62 . 7) (370 . 13) (100 . "AcDbLine") (10 4276.0180995475
6470.5882352941 0.0) (11 6628.9592760181 6470.5882352941 0.0))
((0 . "LINE") (100 . "AcDbEntity") (8 . "ARCH") (62 . 7) (370 . 13) (100 . "AcDbLine") (10 4276.0180995475
6199.0950226244 0.0) (11 6628.9592760181 6199.0950226244 0.0))
((0 . "LINE") (100 . "AcDbEntity") (8 . "ARCH") (62 . 7) (370 . 13) (100 . "AcDbLine") (10 13348.4162895928
6549.7737556561 0.0) (11 13438.9140271493 6549.7737556561 0.0))
((0 . "LINE") (100 . "AcDbEntity") (8 . "ARCH") (62 . 7) (370 . 13) (100 . "AcDbLine") (10 13438.9140271493
6549.7737556561 0.0) (11 15554.2986425339 6549.7737556561 0.0))
((0 . "LINE") (100 . "AcDbEntity") (8 . "ARCH") (62 . 7) (370 . 13) (100 . "AcDbLine") (10 15554.2986425339
6549.7737556561 0.0) (11 15610.8597285068 6549.7737556561 0.0))
((0 . "LINE") (100 . "AcDbEntity") (8 . "ARCH") (62 . 7) (370 . 13) (100 . "AcDbLine") (10 15610.8597285068
6549.7737556561 0.0) (11 15712.6696832579 6549.7737556561 0.0))
((0 . "LINE") (100 . "AcDbEntity") (8 . "ARCH") (62 . 7) (370 . 13) (100 . "AcDbLine") (10 15712.6696832579
6549.7737556561 0.0) (11 15769.2307692308 6549.7737556561 0.0))
((0 . "LINE") (100 . "AcDbEntity") (8 . "ARCH") (62 . 7) (370 . 13) (100 . "AcDbLine") (10 13348.4162895928
6470.5882352941 0.0) (11 15769.2307692308 6470.5882352941 0.0))
((0 . "LINE") (100 . "AcDbEntity") (8 . "ARCH") (62 . 7) (370 . 13) (100 . "AcDbLine") (10 13348.4162895928
6199.0950226244 0.0) (11 15769.2307692308 6199.0950226244 0.0))
((0 . "LINE") (100 . "AcDbEntity") (8 . "ARCH") (62 . 7) (370 . 13) (100 . "AcDbLine") (10 2782.8054298643
6753.3936651584 0.0) (11 4276.0180995475 6753.3936651584 0.0))
((0 . "LINE") (100 . "AcDbEntity") (8 . "ARCH") (62 . 7) (370 . 13) (100 . "AcDbLine") (10 4276.0180995475
6753.3936651584 0.0) (11 4276.0180995475 6549.7737556561 0.0))
((0 . "LINE") (100 . "AcDbEntity") (8 . "ARCH") (62 . 7) (370 . 13) (100 . "AcDbLine") (10 4276.0180995475
6549.7737556561 0.0) (11 4276.0180995475 6481.9004524887 0.0))
((0 . "LINE") (100 . "AcDbEntity") (8 . "ARCH") (62 . 7) (370 . 13) (100 . "AcDbLine") (10 4276.0180995475
6481.9004524887 0.0) (11 2782.8054298643 6481.9004524887 0.0))
((0 . "LINE") (100 . "AcDbEntity") (8 . "ARCH") (62 . 7) (370 . 13) (100 . "AcDbLine") (10 2782.8054298643
6481.9004524887 0.0) (11 2782.8054298643 6549.7737556561 0.0))
((0 . "LINE") (100 . "AcDbEntity") (8 . "ARCH") (62 . 7) (370 . 13) (100 . "AcDbLine") (10 2782.8054298643
6549.7737556561 0.0) (11 2782.8054298643 6753.3936651584 0.0))
((0 . "LINE") (100 . "AcDbEntity") (8 . "ARCH") (62 . 7) (370 . 13) (100 . "AcDbLine") (10 6628.9592760181
6753.3936651584 0.0) (11 7941.1764705882 6753.3936651584 0.0))
((0 . "LINE") (100 . "AcDbEntity") (8 . "ARCH") (62 . 7) (370 . 13) (100 . "AcDbLine") (10 7941.1764705882
6753.3936651584 0.0) (11 7941.1764705882 6481.9004524887 0.0))
((0 . "LINE") (100 . "AcDbEntity") (8 . "ARCH") (62 . 7) (370 . 13) (100 . "AcDbLine") (10 7941.1764705882
6481.9004524887 0.0) (11 7929.8642533937 6481.9004524887 0.0))
((0 . "LINE") (100 . "AcDbEntity") (8 . "ARCH") (62 . 7) (370 . 13) (100 . "AcDbLine") (10 7929.8642533937
6481.9004524887 0.0) (11 6628.9592760181 6481.9004524887 0.0))
((0 . "LINE") (100 . "AcDbEntity") (8 . "ARCH") (62 . 7) (370 . 13) (100 . "AcDbLine") (10 6628.9592760181
6481.9004524887 0.0) (11 6628.9592760181 6549.7737556561 0.0))
((0 . "LINE") (100 . "AcDbEntity") (8 . "ARCH") (62 . 7) (370 . 13) (100 . "AcDbLine") (10 6628.9592760181
6549.7737556561 0.0) (11 6628.9592760181 6753.3936651584 0.0))
((0 . "LINE") (100 . "AcDbEntity") (8 . "ARCH") (62 . 7) (370 . 13) (100 . "AcDbLine") (10 12036.1990950226
6753.3936651584 0.0) (11 13348.4162895928 6753.3936651584 0.0))
((0 . "LINE") (100 . "AcDbEntity") (8 . "ARCH") (62 . 7) (370 . 13) (100 . "AcDbLine") (10 13348.4162895928
6753.3936651584 0.0) (11 13348.4162895928 6549.7737556561 0.0))
((0 . "LINE") (100 . "AcDbEntity") (8 . "ARCH") (62 . 7) (370 . 13) (100 . "AcDbLine") (10 13348.4162895928
6549.7737556561 0.0) (11 13348.4162895928 6481.9004524887 0.0))
((0 . "LINE") (100 . "AcDbEntity") (8 . "ARCH") (62 . 7) (370 . 13) (100 . "AcDbLine") (10 13348.4162895928
6481.9004524887 0.0) (11 12036.1990950226 6481.9004524887 0.0))
((0 . "LINE") (100 . "AcDbEntity") (8 . "ARCH") (62 . 7) (370 . 13) (100 . "AcDbLine") (10 12036.1990950226
6481.9004524887 0.0) (11 12036.1990950226 6549.7737556561 0.0))
((0 . "LINE") (100 . "AcDbEntity") (8 . "ARCH") (62 . 7) (370 . 13) (100 . "AcDbLine") (10 12036.1990950226
6549.7737556561 0.0) (11 12036.1990950226 6753.3936651584 0.0))
((0 . "LINE") (100 . "AcDbEntity") (8 . "ARCH") (62 . 7) (370 . 13) (100 . "AcDbLine") (10 15769.2307692308
6753.3936651584 0.0) (11 17239.8190045249 6753.3936651584 0.0))
((0 . "LINE") (100 . "AcDbEntity") (8 . "ARCH") (62 . 7) (370 . 13) (100 . "AcDbLine") (10 17239.8190045249
6753.3936651584 0.0) (11 17239.8190045249 6549.7737556561 0.0))
((0 . "LINE") (100 . "AcDbEntity") (8 . "ARCH") (62 . 7) (370 . 13) (100 . "AcDbLine") (10 17239.8190045249
6549.7737556561 0.0) (11 17239.8190045249 6481.9004524887 0.0))
((0 . "LINE") (100 . "AcDbEntity") (8 . "ARCH") (62 . 7) (370 . 13) (100 . "AcDbLine") (10 17239.8190045249
6481.9004524887 0.0) (11 15769.2307692308 6481.9004524887 0.0))
((0 . "LINE") (100 . "AcDbEntity") (8 . "ARCH") (62 . 7) (370 . 13) (100 . "AcDbLine") (10 15769.2307692308
6481.9004524887 0.0) (11 15769.2307692308 6549.7737556561 0.0))
((0 . "LINE") (100 . "AcDbEntity") (8 . "ARCH") (62 . 7) (370 . 13) (100 . "AcDbLine") (10 15769.2307692308
6549.7737556561 0.0) (11 15769.2307692308 6753.3936651584 0.0))
((0 . "LINE") (100 . "AcDbEntity") (8 . "ARCH") (62 . 7) (370 . 13) (100 . "AcDbLine") (10 2952.4886877828
7952.4886877828 0.0) (11 3710.407239819 7952.4886877828 0.0))
((0 . "LINE") (100 . "AcDbEntity") (8 . "ARCH") (62 . 7) (370 . 13) (100 . "AcDbLine") (10 3710.407239819
7952.4886877828 0.0) (11 3710.407239819 7828.0542986425 0.0))
((0 . "LINE") (100 . "AcDbEntity") (8 . "ARCH") (62 . 7) (370 . 13) (100 . "AcDbLine") (10 3710.407239819
7828.0542986425 0.0) (11 3710.407239819 7760.1809954751 0.0))
((0 . "LINE") (100 . "AcDbEntity") (8 . "ARCH") (62 . 7) (370 . 13) (100 . "AcDbLine") (10 3710.407239819
7760.1809954751 0.0) (11 3710.407239819 7635.7466063348 0.0))
((0 . "LINE") (100 . "AcDbEntity") (8 . "ARCH") (62 . 7) (370 . 13) (100 . "AcDbLine") (10 3710.407239819
7635.7466063348 0.0) (11 2952.4886877828 7635.7466063348 0.0))
((0 . "LINE") (100 . "AcDbEntity") (8 . "ARCH") (62 . 7) (370 . 13) (100 . "AcDbLine") (10 2952.4886877828
7635.7466063348 0.0) (11 2952.4886877828 7952.4886877828 0.0))
((0 . "LINE") (100 . "AcDbEntity") (8 . "ARCH") (62 . 7) (370 . 13) (100 . "AcDbLine") (10 2952.4886877828
7601.8099547511 0.0) (11 3710.407239819 7601.8099547511 0.0))
((0 . "LINE") (100 . "AcDbEntity") (8 . "ARCH") (62 . 7) (370 . 13) (100 . "AcDbLine") (10 2952.4886877828
7635.7466063348 0.0) (11 2952.4886877828 7601.8099547511 0.0))
((0 . "LINE") (100 . "AcDbEntity") (8 . "ARCH") (62 . 7) (370 . 13) (100 . "AcDbLine") (10 2952.4886877828
7601.8099547511 0.0) (11 2952.4886877828 6832.5791855204 0.0))
((0 . "LINE") (100 . "AcDbEntity") (8 . "ARCH") (62 . 7) (370 . 13) (100 . "AcDbLine") (10 3710.407239819
7635.7466063348 0.0) (11 3710.407239819 7601.8099547511 0.0))
((0 . "LINE") (100 . "AcDbEntity") (8 . "ARCH") (62 . 7) (370 . 13) (100 . "AcDbLine") (10 3710.407239819
7601.8099547511 0.0) (11 3710.407239819 7567.8733031674 0.0))
((0 . "LINE") (100 . "AcDbEntity") (8 . "ARCH") (62 . 7) (370 . 13) (100 . "AcDbLine") (10 3710.407239819
7567.8733031674 0.0) (11 3710.407239819 6832.5791855204 0.0))
((0 . "LINE") (100 . "AcDbEntity") (8 . "ARCH") (62 . 7) (370 . 13) (100 . "AcDbLine") (10 2895.92760181 8178.7330316742
0.0) (11 3789.592760181 8178.7330316742 0.0))
((0 . "LINE") (100 . "AcDbEntity") (8 . "ARCH") (62 . 7) (370 . 13) (100 . "AcDbLine") (10 3789.592760181
8178.7330316742 0.0) (11 3789.592760181 8076.9230769231 0.0))
((0 . "LINE") (100 . "AcDbEntity") (8 . "ARCH") (62 . 7) (370 . 13) (100 . "AcDbLine") (10 3789.592760181
8076.9230769231 0.0) (11 3755.6561085973 8076.9230769231 0.0))
((0 . "LINE") (100 . "AcDbEntity") (8 . "ARCH") (62 . 7) (370 . 13) (100 . "AcDbLine") (10 3755.6561085973
8076.9230769231 0.0) (11 3753.3936651584 8065.6108597285 0.0))
((0 . "LINE") (100 . "AcDbEntity") (8 . "ARCH") (62 . 7) (370 . 13) (100 . "AcDbLine") (10 3753.3936651584
8065.6108597285 0.0) (11 3744.3438914027 8020.3619909502 0.0))
((0 . "LINE") (100 . "AcDbEntity") (8 . "ARCH") (62 . 7) (370 . 13) (100 . "AcDbLine") (10 3744.3438914027
8020.3619909502 0.0) (11 3730.7692307692 7997.7375565611 0.0))
((0 . "LINE") (100 . "AcDbEntity") (8 . "ARCH") (62 . 7) (370 . 13) (100 . "AcDbLine") (10 3730.7692307692
7997.7375565611 0.0) (11 3710.407239819 7963.8009049774 0.0))
((0 . "LINE") (100 . "AcDbEntity") (8 . "ARCH") (62 . 7) (370 . 13) (100 . "AcDbLine") (10 3710.407239819
7963.8009049774 0.0) (11 2952.4886877828 7963.8009049774 0.0))
((0 . "LINE") (100 . "AcDbEntity") (8 . "ARCH") (62 . 7) (370 . 13) (100 . "AcDbLine") (10 2952.4886877828
7963.8009049774 0.0) (11 2938.9140271493 7997.7375565611 0.0))
((0 . "LINE") (100 . "AcDbEntity") (8 . "ARCH") (62 . 7) (370 . 13) (100 . "AcDbLine") (10 2938.9140271493
7997.7375565611 0.0) (11 2929.8642533937 8020.3619909502 0.0))
((0 . "LINE") (100 . "AcDbEntity") (8 . "ARCH") (62 . 7) (370 . 13) (100 . "AcDbLine") (10 2929.8642533937
8020.3619909502 0.0) (11 2907.2398190045 8065.6108597285 0.0))
((0 . "LINE") (100 . "AcDbEntity") (8 . "ARCH") (62 . 7) (370 . 13) (100 . "AcDbLine") (10 2907.2398190045
8065.6108597285 0.0) (11 2895.92760181 8065.6108597285 0.0))
((0 . "LINE") (100 . "AcDbEntity") (8 . "ARCH") (62 . 7) (370 . 13) (100 . "AcDbLine") (10 2895.92760181 8065.6108597285
0.0) (11 2895.92760181 8178.7330316742 0.0))
((0 . "LINE") (100 . "AcDbEntity") (8 . "ARCH") (62 . 7) (370 . 13) (100 . "AcDbLine") (10 2907.2398190045
8065.6108597285 0.0) (11 3753.3936651584 8065.6108597285 0.0))
((0 . "LINE") (100 . "AcDbEntity") (8 . "ARCH") (62 . 7) (370 . 13) (100 . "AcDbLine") (10 3753.3936651584
8065.6108597285 0.0) (11 3778.2805429864 8065.6108597285 0.0))
((0 . "LINE") (100 . "AcDbEntity") (8 . "ARCH") (62 . 7) (370 . 13) (100 . "AcDbLine") (10 2938.9140271493
7997.7375565611 0.0) (11 3730.7692307692 7997.7375565611 0.0))
((0 . "LINE") (100 . "AcDbEntity") (8 . "ARCH") (62 . 7) (370 . 13) (100 . "AcDbLine") (10 16334.8416289593
7952.4886877828 0.0) (11 17092.7601809955 7952.4886877828 0.0))
((0 . "LINE") (100 . "AcDbEntity") (8 . "ARCH") (62 . 7) (370 . 13) (100 . "AcDbLine") (10 17092.7601809955
7952.4886877828 0.0) (11 17092.7601809955 7635.7466063348 0.0))
((0 . "LINE") (100 . "AcDbEntity") (8 . "ARCH") (62 . 7) (370 . 13) (100 . "AcDbLine") (10 17092.7601809955
7635.7466063348 0.0) (11 16334.8416289593 7635.7466063348 0.0))
((0 . "LINE") (100 . "AcDbEntity") (8 . "ARCH") (62 . 7) (370 . 13) (100 . "AcDbLine") (10 16334.8416289593
7635.7466063348 0.0) (11 16334.8416289593 7760.1809954751 0.0))
((0 . "LINE") (100 . "AcDbEntity") (8 . "ARCH") (62 . 7) (370 . 13) (100 . "AcDbLine") (10 16334.8416289593
7760.1809954751 0.0) (11 16334.8416289593 7828.0542986425 0.0))
((0 . "LINE") (100 . "AcDbEntity") (8 . "ARCH") (62 . 7) (370 . 13) (100 . "AcDbLine") (10 16334.8416289593
7828.0542986425 0.0) (11 16334.8416289593 7952.4886877828 0.0))
((0 . "LINE") (100 . "AcDbEntity") (8 . "ARCH") (62 . 7) (370 . 13) (100 . "AcDbLine") (10 16334.8416289593
7601.8099547511 0.0) (11 17092.7601809955 7601.8099547511 0.0))
((0 . "LINE") (100 . "AcDbEntity") (8 . "ARCH") (62 . 7) (370 . 13) (100 . "AcDbLine") (10 16334.8416289593
7635.7466063348 0.0) (11 16334.8416289593 7601.8099547511 0.0))
((0 . "LINE") (100 . "AcDbEntity") (8 . "ARCH") (62 . 7) (370 . 13) (100 . "AcDbLine") (10 16334.8416289593
7601.8099547511 0.0) (11 16334.8416289593 7567.8733031674 0.0))
((0 . "LINE") (100 . "AcDbEntity") (8 . "ARCH") (62 . 7) (370 . 13) (100 . "AcDbLine") (10 16334.8416289593
7567.8733031674 0.0) (11 16334.8416289593 6832.5791855204 0.0))
((0 . "LINE") (100 . "AcDbEntity") (8 . "ARCH") (62 . 7) (370 . 13) (100 . "AcDbLine") (10 17092.7601809955
7635.7466063348 0.0) (11 17092.7601809955 7601.8099547511 0.0))
((0 . "LINE") (100 . "AcDbEntity") (8 . "ARCH") (62 . 7) (370 . 13) (100 . "AcDbLine") (10 17092.7601809955
7601.8099547511 0.0) (11 17092.7601809955 6832.5791855204 0.0))
((0 . "LINE") (100 . "AcDbEntity") (8 . "ARCH") (62 . 7) (370 . 13) (100 . "AcDbLine") (10 16278.2805429864
8178.7330316742 0.0) (11 17171.9457013575 8178.7330316742 0.0))
((0 . "LINE") (100 . "AcDbEntity") (8 . "ARCH") (62 . 7) (370 . 13) (100 . "AcDbLine") (10 17171.9457013575
8178.7330316742 0.0) (11 17171.9457013575 8076.9230769231 0.0))
((0 . "LINE") (100 . "AcDbEntity") (8 . "ARCH") (62 . 7) (370 . 13) (100 . "AcDbLine") (10 17171.9457013575
8076.9230769231 0.0) (11 17138.0090497738 8076.9230769231 0.0))
((0 . "LINE") (100 . "AcDbEntity") (8 . "ARCH") (62 . 7) (370 . 13) (100 . "AcDbLine") (10 17138.0090497738
8076.9230769231 0.0) (11 17135.7466063348 8065.6108597285 0.0))
((0 . "LINE") (100 . "AcDbEntity") (8 . "ARCH") (62 . 7) (370 . 13) (100 . "AcDbLine") (10 17135.7466063348
8065.6108597285 0.0) (11 17126.6968325792 8020.3619909502 0.0))
((0 . "LINE") (100 . "AcDbEntity") (8 . "ARCH") (62 . 7) (370 . 13) (100 . "AcDbLine") (10 17126.6968325792
8020.3619909502 0.0) (11 17113.1221719457 7997.7375565611 0.0))
((0 . "LINE") (100 . "AcDbEntity") (8 . "ARCH") (62 . 7) (370 . 13) (100 . "AcDbLine") (10 17113.1221719457
7997.7375565611 0.0) (11 17092.7601809955 7963.8009049774 0.0))
((0 . "LINE") (100 . "AcDbEntity") (8 . "ARCH") (62 . 7) (370 . 13) (100 . "AcDbLine") (10 17092.7601809955
7963.8009049774 0.0) (11 16334.8416289593 7963.8009049774 0.0))
((0 . "LINE") (100 . "AcDbEntity") (8 . "ARCH") (62 . 7) (370 . 13) (100 . "AcDbLine") (10 16334.8416289593
7963.8009049774 0.0) (11 16321.2669683258 7997.7375565611 0.0))
((0 . "LINE") (100 . "AcDbEntity") (8 . "ARCH") (62 . 7) (370 . 13) (100 . "AcDbLine") (10 16321.2669683258
7997.7375565611 0.0) (11 16312.2171945701 8020.3619909502 0.0))
((0 . "LINE") (100 . "AcDbEntity") (8 . "ARCH") (62 . 7) (370 . 13) (100 . "AcDbLine") (10 16312.2171945701
8020.3619909502 0.0) (11 16289.592760181 8065.6108597285 0.0))
((0 . "LINE") (100 . "AcDbEntity") (8 . "ARCH") (62 . 7) (370 . 13) (100 . "AcDbLine") (10 16289.592760181
8065.6108597285 0.0) (11 16278.2805429864 8065.6108597285 0.0))
((0 . "LINE") (100 . "AcDbEntity") (8 . "ARCH") (62 . 7) (370 . 13) (100 . "AcDbLine") (10 16278.2805429864
8065.6108597285 0.0) (11 16278.2805429864 8178.7330316742 0.0))
((0 . "LINE") (100 . "AcDbEntity") (8 . "ARCH") (62 . 7) (370 . 13) (100 . "AcDbLine") (10 16289.592760181
8065.6108597285 0.0) (11 17135.7466063348 8065.6108597285 0.0))
((0 . "LINE") (100 . "AcDbEntity") (8 . "ARCH") (62 . 7) (370 . 13) (100 . "AcDbLine") (10 17135.7466063348
8065.6108597285 0.0) (11 17160.6334841629 8065.6108597285 0.0))
((0 . "LINE") (100 . "AcDbEntity") (8 . "ARCH") (62 . 7) (370 . 13) (100 . "AcDbLine") (10 16321.2669683258
7997.7375565611 0.0) (11 17113.1221719457 7997.7375565611 0.0))
((0 . "LINE") (100 . "AcDbEntity") (8 . "ARCH") (62 . 7) (370 . 13) (100 . "AcDbLine") (10 3710.407239819
7828.0542986425 0.0) (11 7307.6923076923 7828.0542986425 0.0))
((0 . "LINE") (100 . "AcDbEntity") (8 . "ARCH") (62 . 7) (370 . 13) (100 . "AcDbLine") (10 7307.6923076923
7828.0542986425 0.0) (11 7330.3167420814 7828.0542986425 0.0))
((0 . "LINE") (100 . "AcDbEntity") (8 . "ARCH") (62 . 7) (370 . 13) (100 . "AcDbLine") (10 3710.407239819
7760.1809954751 0.0) (11 7330.3167420814 7760.1809954751 0.0))
((0 . "LINE") (100 . "AcDbEntity") (8 . "ARCH") (62 . 7) (370 . 13) (100 . "AcDbLine") (10 3710.407239819
7635.7466063348 0.0) (11 7330.3167420814 7635.7466063348 0.0))
((0 . "LINE") (100 . "AcDbEntity") (8 . "ARCH") (62 . 7) (370 . 13) (100 . "AcDbLine") (10 3710.407239819
7567.8733031674 0.0) (11 4434.3891402715 7567.8733031674 0.0))
((0 . "LINE") (100 . "AcDbEntity") (8 . "ARCH") (62 . 7) (370 . 13) (100 . "AcDbLine") (10 4434.3891402715
7567.8733031674 0.0) (11 4490.9502262443 7567.8733031674 0.0))
((0 . "LINE") (100 . "AcDbEntity") (8 . "ARCH") (62 . 7) (370 . 13) (100 . "AcDbLine") (10 4490.9502262443
7567.8733031674 0.0) (11 7330.3167420814 7567.8733031674 0.0))
((0 . "LINE") (100 . "AcDbEntity") (8 . "ARCH") (62 . 7) (370 . 13) (100 . "AcDbLine") (10 7714.9321266968
7828.0542986425 0.0) (11 7726.2443438914 7828.0542986425 0.0))
((0 . "LINE") (100 . "AcDbEntity") (8 . "ARCH") (62 . 7) (370 . 13) (100 . "AcDbLine") (10 7726.2443438914
7828.0542986425 0.0) (11 8947.963800905 7828.0542986425 0.0))
((0 . "LINE") (100 . "AcDbEntity") (8 . "ARCH") (62 . 7) (370 . 13) (100 . "AcDbLine") (10 7714.9321266968
7760.1809954751 0.0) (11 8947.963800905 7760.1809954751 0.0))
((0 . "LINE") (100 . "AcDbEntity") (8 . "ARCH") (62 . 7) (370 . 13) (100 . "AcDbLine") (10 7714.9321266968
7635.7466063348 0.0) (11 8947.963800905 7635.7466063348 0.0))
((0 . "LINE") (100 . "AcDbEntity") (8 . "ARCH") (62 . 7) (370 . 13) (100 . "AcDbLine") (10 7714.9321266968
7567.8733031674 0.0) (11 8947.963800905 7567.8733031674 0.0))
((0 . "LINE") (100 . "AcDbEntity") (8 . "ARCH") (62 . 7) (370 . 13) (100 . "AcDbLine") (10 9807.6923076923
7828.0542986425 0.0) (11 10316.742081448 7828.0542986425 0.0))
((0 . "LINE") (100 . "AcDbEntity") (8 . "ARCH") (62 . 7) (370 . 13) (100 . "AcDbLine") (10 9807.6923076923
7760.1809954751 0.0) (11 10316.742081448 7760.1809954751 0.0))
((0 . "LINE") (100 . "AcDbEntity") (8 . "ARCH") (62 . 7) (370 . 13) (100 . "AcDbLine") (10 9807.6923076923
7635.7466063348 0.0) (11 10316.742081448 7635.7466063348 0.0))
((0 . "LINE") (100 . "AcDbEntity") (8 . "ARCH") (62 . 7) (370 . 13) (100 . "AcDbLine") (10 9807.6923076923
7567.8733031674 0.0) (11 10316.742081448 7567.8733031674 0.0))
((0 . "LINE") (100 . "AcDbEntity") (8 . "ARCH") (62 . 7) (370 . 13) (100 . "AcDbLine") (10 11085.9728506787
7828.0542986425 0.0) (11 12126.6968325792 7828.0542986425 0.0))
((0 . "LINE") (100 . "AcDbEntity") (8 . "ARCH") (62 . 7) (370 . 13) (100 . "AcDbLine") (10 12126.6968325792
7828.0542986425 0.0) (11 12149.3212669683 7828.0542986425 0.0))
((0 . "LINE") (100 . "AcDbEntity") (8 . "ARCH") (62 . 7) (370 . 13) (100 . "AcDbLine") (10 11085.9728506787
7760.1809954751 0.0) (11 12149.3212669683 7760.1809954751 0.0))
((0 . "LINE") (100 . "AcDbEntity") (8 . "ARCH") (62 . 7) (370 . 13) (100 . "AcDbLine") (10 11085.9728506787
7635.7466063348 0.0) (11 12149.3212669683 7635.7466063348 0.0))
((0 . "LINE") (100 . "AcDbEntity") (8 . "ARCH") (62 . 7) (370 . 13) (100 . "AcDbLine") (10 11085.9728506787
7567.8733031674 0.0) (11 12149.3212669683 7567.8733031674 0.0))
((0 . "LINE") (100 . "AcDbEntity") (8 . "ARCH") (62 . 7) (370 . 13) (100 . "AcDbLine") (10 12590.4977375566
7828.0542986425 0.0) (11 12601.8099547511 7828.0542986425 0.0))
((0 . "LINE") (100 . "AcDbEntity") (8 . "ARCH") (62 . 7) (370 . 13) (100 . "AcDbLine") (10 12601.8099547511
7828.0542986425 0.0) (11 16334.8416289593 7828.0542986425 0.0))
((0 . "LINE") (100 . "AcDbEntity") (8 . "ARCH") (62 . 7) (370 . 13) (100 . "AcDbLine") (10 12590.4977375566
7760.1809954751 0.0) (11 16334.8416289593 7760.1809954751 0.0))
((0 . "LINE") (100 . "AcDbEntity") (8 . "ARCH") (62 . 7) (370 . 13) (100 . "AcDbLine") (10 12590.4977375566
7635.7466063348 0.0) (11 16334.8416289593 7635.7466063348 0.0))
((0 . "LINE") (100 . "AcDbEntity") (8 . "ARCH") (62 . 7) (370 . 13) (100 . "AcDbLine") (10 12590.4977375566
7567.8733031674 0.0) (11 15554.2986425339 7567.8733031674 0.0))
((0 . "LINE") (100 . "AcDbEntity") (8 . "ARCH") (62 . 7) (370 . 13) (100 . "AcDbLine") (10 15554.2986425339
7567.8733031674 0.0) (11 15610.8597285068 7567.8733031674 0.0))
((0 . "LINE") (100 . "AcDbEntity") (8 . "ARCH") (62 . 7) (370 . 13) (100 . "AcDbLine") (10 15610.8597285068
7567.8733031674 0.0) (11 16334.8416289593 7567.8733031674 0.0))
((0 . "LINE") (100 . "AcDbEntity") (8 . "ARCH") (62 . 7) (370 . 13) (100 . "AcDbLine") (10 7307.6923076923
7861.9909502262 0.0) (11 7726.2443438914 7861.9909502262 0.0))
((0 . "LINE") (100 . "AcDbEntity") (8 . "ARCH") (62 . 7) (370 . 13) (100 . "AcDbLine") (10 7726.2443438914
7861.9909502262 0.0) (11 7726.2443438914 7828.0542986425 0.0))
((0 . "LINE") (100 . "AcDbEntity") (8 . "ARCH") (62 . 7) (370 . 13) (100 . "AcDbLine") (10 7726.2443438914
7828.0542986425 0.0) (11 7726.2443438914 7771.4932126697 0.0))
((0 . "LINE") (100 . "AcDbEntity") (8 . "ARCH") (62 . 7) (370 . 13) (100 . "AcDbLine") (10 7726.2443438914
7771.4932126697 0.0) (11 7714.9321266968 7771.4932126697 0.0))
((0 . "LINE") (100 . "AcDbEntity") (8 . "ARCH") (62 . 7) (370 . 13) (100 . "AcDbLine") (10 7714.9321266968
7771.4932126697 0.0) (11 7330.3167420814 7771.4932126697 0.0))
((0 . "LINE") (100 . "AcDbEntity") (8 . "ARCH") (62 . 7) (370 . 13) (100 . "AcDbLine") (10 7330.3167420814
7771.4932126697 0.0) (11 7307.6923076923 7771.4932126697 0.0))
((0 . "LINE") (100 . "AcDbEntity") (8 . "ARCH") (62 . 7) (370 . 13) (100 . "AcDbLine") (10 7307.6923076923
7771.4932126697 0.0) (11 7307.6923076923 7828.0542986425 0.0))
((0 . "LINE") (100 . "AcDbEntity") (8 . "ARCH") (62 . 7) (370 . 13) (100 . "AcDbLine") (10 7307.6923076923
7828.0542986425 0.0) (11 7307.6923076923 7861.9909502262 0.0))
((0 . "LINE") (100 . "AcDbEntity") (8 . "ARCH") (62 . 7) (370 . 13) (100 . "AcDbLine") (10 7714.9321266968
7771.4932126697 0.0) (11 7714.9321266968 7760.1809954751 0.0))
((0 . "LINE") (100 . "AcDbEntity") (8 . "ARCH") (62 . 7) (370 . 13) (100 . "AcDbLine") (10 7714.9321266968
7760.1809954751 0.0) (11 7714.9321266968 7635.7466063348 0.0))
((0 . "LINE") (100 . "AcDbEntity") (8 . "ARCH") (62 . 7) (370 . 13) (100 . "AcDbLine") (10 7714.9321266968
7635.7466063348 0.0) (11 7714.9321266968 7624.4343891403 0.0))
((0 . "LINE") (100 . "AcDbEntity") (8 . "ARCH") (62 . 7) (370 . 13) (100 . "AcDbLine") (10 7714.9321266968
7624.4343891403 0.0) (11 7330.3167420814 7624.4343891403 0.0))
((0 . "LINE") (100 . "AcDbEntity") (8 . "ARCH") (62 . 7) (370 . 13) (100 . "AcDbLine") (10 7330.3167420814
7624.4343891403 0.0) (11 7330.3167420814 7635.7466063348 0.0))
((0 . "LINE") (100 . "AcDbEntity") (8 . "ARCH") (62 . 7) (370 . 13) (100 . "AcDbLine") (10 7330.3167420814
7635.7466063348 0.0) (11 7330.3167420814 7760.1809954751 0.0))
((0 . "LINE") (100 . "AcDbEntity") (8 . "ARCH") (62 . 7) (370 . 13) (100 . "AcDbLine") (10 7330.3167420814
7760.1809954751 0.0) (11 7330.3167420814 7771.4932126697 0.0))
((0 . "LINE") (100 . "AcDbEntity") (8 . "ARCH") (62 . 7) (370 . 13) (100 . "AcDbLine") (10 7330.3167420814
7567.8733031674 0.0) (11 7714.9321266968 7567.8733031674 0.0))
((0 . "LINE") (100 . "AcDbEntity") (8 . "ARCH") (62 . 7) (370 . 13) (100 . "AcDbLine") (10 7330.3167420814
7567.8733031674 0.0) (11 7330.3167420814 6832.5791855204 0.0))
((0 . "LINE") (100 . "AcDbEntity") (8 . "ARCH") (62 . 7) (370 . 13) (100 . "AcDbLine") (10 7714.9321266968
7567.8733031674 0.0) (11 7714.9321266968 6832.5791855204 0.0))
((0 . "LINE") (100 . "AcDbEntity") (8 . "ARCH") (62 . 7) (370 . 13) (100 . "AcDbLine") (10 12126.6968325792
7861.9909502262 0.0) (11 12601.8099547511 7861.9909502262 0.0))
((0 . "LINE") (100 . "AcDbEntity") (8 . "ARCH") (62 . 7) (370 . 13) (100 . "AcDbLine") (10 12601.8099547511
7861.9909502262 0.0) (11 12601.8099547511 7828.0542986425 0.0))
((0 . "LINE") (100 . "AcDbEntity") (8 . "ARCH") (62 . 7) (370 . 13) (100 . "AcDbLine") (10 12601.8099547511
7828.0542986425 0.0) (11 12601.8099547511 7771.4932126697 0.0))
((0 . "LINE") (100 . "AcDbEntity") (8 . "ARCH") (62 . 7) (370 . 13) (100 . "AcDbLine") (10 12601.8099547511
7771.4932126697 0.0) (11 12590.4977375566 7771.4932126697 0.0))
((0 . "LINE") (100 . "AcDbEntity") (8 . "ARCH") (62 . 7) (370 . 13) (100 . "AcDbLine") (10 12590.4977375566
7771.4932126697 0.0) (11 12149.3212669683 7771.4932126697 0.0))
((0 . "LINE") (100 . "AcDbEntity") (8 . "ARCH") (62 . 7) (370 . 13) (100 . "AcDbLine") (10 12149.3212669683
7771.4932126697 0.0) (11 12126.6968325792 7771.4932126697 0.0))
((0 . "LINE") (100 . "AcDbEntity") (8 . "ARCH") (62 . 7) (370 . 13) (100 . "AcDbLine") (10 12126.6968325792
7771.4932126697 0.0) (11 12126.6968325792 7828.0542986425 0.0))
((0 . "LINE") (100 . "AcDbEntity") (8 . "ARCH") (62 . 7) (370 . 13) (100 . "AcDbLine") (10 12126.6968325792
7828.0542986425 0.0) (11 12126.6968325792 7861.9909502262 0.0))
((0 . "LINE") (100 . "AcDbEntity") (8 . "ARCH") (62 . 7) (370 . 13) (100 . "AcDbLine") (10 12590.4977375566
7771.4932126697 0.0) (11 12590.4977375566 7760.1809954751 0.0))
((0 . "LINE") (100 . "AcDbEntity") (8 . "ARCH") (62 . 7) (370 . 13) (100 . "AcDbLine") (10 12590.4977375566
7760.1809954751 0.0) (11 12590.4977375566 7635.7466063348 0.0))
((0 . "LINE") (100 . "AcDbEntity") (8 . "ARCH") (62 . 7) (370 . 13) (100 . "AcDbLine") (10 12590.4977375566
7635.7466063348 0.0) (11 12590.4977375566 7624.4343891403 0.0))
((0 . "LINE") (100 . "AcDbEntity") (8 . "ARCH") (62 . 7) (370 . 13) (100 . "AcDbLine") (10 12590.4977375566
7624.4343891403 0.0) (11 12149.3212669683 7624.4343891403 0.0))
((0 . "LINE") (100 . "AcDbEntity") (8 . "ARCH") (62 . 7) (370 . 13) (100 . "AcDbLine") (10 12149.3212669683
7624.4343891403 0.0) (11 12149.3212669683 7635.7466063348 0.0))
((0 . "LINE") (100 . "AcDbEntity") (8 . "ARCH") (62 . 7) (370 . 13) (100 . "AcDbLine") (10 12149.3212669683
7635.7466063348 0.0) (11 12149.3212669683 7760.1809954751 0.0))
((0 . "LINE") (100 . "AcDbEntity") (8 . "ARCH") (62 . 7) (370 . 13) (100 . "AcDbLine") (10 12149.3212669683
7760.1809954751 0.0) (11 12149.3212669683 7771.4932126697 0.0))
((0 . "LINE") (100 . "AcDbEntity") (8 . "ARCH") (62 . 7) (370 . 13) (100 . "AcDbLine") (10 12149.3212669683
7567.8733031674 0.0) (11 12590.4977375566 7567.8733031674 0.0))
((0 . "LINE") (100 . "AcDbEntity") (8 . "ARCH") (62 . 7) (370 . 13) (100 . "AcDbLine") (10 12149.3212669683
7567.8733031674 0.0) (11 12149.3212669683 6832.5791855204 0.0))
((0 . "LINE") (100 . "AcDbEntity") (8 . "ARCH") (62 . 7) (370 . 13) (100 . "AcDbLine") (10 12590.4977375566
7567.8733031674 0.0) (11 12590.4977375566 6832.5791855204 0.0))
((0 . "LINE") (100 . "AcDbEntity") (8 . "ARCH") (62 . 7) (370 . 13) (100 . "AcDbLine") (10 4434.3891402715
7567.8733031674 0.0) (11 4434.3891402715 6549.7737556561 0.0))
((0 . "LINE") (100 . "AcDbEntity") (8 . "ARCH") (62 . 7) (370 . 13) (100 . "AcDbLine") (10 4490.9502262443
7567.8733031674 0.0) (11 4490.9502262443 6549.7737556561 0.0))
((0 . "LINE") (100 . "AcDbEntity") (8 . "ARCH") (62 . 7) (370 . 13) (100 . "AcDbLine") (10 15554.2986425339
7567.8733031674 0.0) (11 15554.2986425339 6549.7737556561 0.0))
((0 . "LINE") (100 . "AcDbEntity") (8 . "ARCH") (62 . 7) (370 . 13) (100 . "AcDbLine") (10 15610.8597285068
7567.8733031674 0.0) (11 15610.8597285068 6549.7737556561 0.0))
((0 . "LINE") (100 . "AcDbEntity") (8 . "ARCH") (62 . 7) (370 . 13) (100 . "AcDbLine") (10 8947.963800905
7647.0588235294 0.0) (11 9807.6923076923 7647.0588235294 0.0))
((0 . "LINE") (100 . "AcDbEntity") (8 . "ARCH") (62 . 7) (370 . 13) (100 . "AcDbLine") (10 9807.6923076923
7647.0588235294 0.0) (11 9807.6923076923 7635.7466063348 0.0))
((0 . "LINE") (100 . "AcDbEntity") (8 . "ARCH") (62 . 7) (370 . 13) (100 . "AcDbLine") (10 9807.6923076923
7635.7466063348 0.0) (11 9807.6923076923 7567.8733031674 0.0))
((0 . "LINE") (100 . "AcDbEntity") (8 . "ARCH") (62 . 7) (370 . 13) (100 . "AcDbLine") (10 9807.6923076923
7567.8733031674 0.0) (11 9807.6923076923 6809.9547511312 0.0))
((0 . "LINE") (100 . "AcDbEntity") (8 . "ARCH") (62 . 7) (370 . 13) (100 . "AcDbLine") (10 8947.963800905
6549.7737556561 0.0) (11 8947.963800905 7567.8733031674 0.0))
((0 . "LINE") (100 . "AcDbEntity") (8 . "ARCH") (62 . 7) (370 . 13) (100 . "AcDbLine") (10 8947.963800905
7567.8733031674 0.0) (11 8947.963800905 7635.7466063348 0.0))
((0 . "LINE") (100 . "AcDbEntity") (8 . "ARCH") (62 . 7) (370 . 13) (100 . "AcDbLine") (10 8947.963800905
7635.7466063348 0.0) (11 8947.963800905 7647.0588235294 0.0))
((0 . "LINE") (100 . "AcDbEntity") (8 . "ARCH") (62 . 7) (370 . 13) (100 . "AcDbLine") (10 9004.5248868778
7601.8099547511 0.0) (11 9751.1312217195 7601.8099547511 0.0))
((0 . "LINE") (100 . "AcDbEntity") (8 . "ARCH") (62 . 7) (370 . 13) (100 . "AcDbLine") (10 9751.1312217195
7601.8099547511 0.0) (11 9751.1312217195 6809.9547511312 0.0))
((0 . "LINE") (100 . "AcDbEntity") (8 . "ARCH") (62 . 7) (370 . 13) (100 . "AcDbLine") (10 9004.5248868778
6549.7737556561 0.0) (11 9004.5248868778 7601.8099547511 0.0))
((0 . "LINE") (100 . "AcDbEntity") (8 . "ARCH") (62 . 7) (370 . 13) (100 . "AcDbLine") (10 9106.334841629 7500 0.0) (11
9649.3212669683 7500 0.0))
((0 . "LINE") (100 . "AcDbEntity") (8 . "ARCH") (62 . 7) (370 . 13) (100 . "AcDbLine") (10 9649.3212669683 7500 0.0) (11
9649.3212669683 6866.5158371041 0.0))
((0 . "LINE") (100 . "AcDbEntity") (8 . "ARCH") (62 . 7) (370 . 13) (100 . "AcDbLine") (10 9649.3212669683
6866.5158371041 0.0) (11 9106.334841629 6866.5158371041 0.0))
((0 . "LINE") (100 . "AcDbEntity") (8 . "ARCH") (62 . 7) (370 . 13) (100 . "AcDbLine") (10 9106.334841629
6866.5158371041 0.0) (11 9106.334841629 7500 0.0))
((0 . "LINE") (100 . "AcDbEntity") (8 . "ARCH") (62 . 7) (370 . 13) (100 . "AcDbLine") (10 9151.5837104072
7454.7511312217 0.0) (11 9604.07239819 7454.7511312217 0.0))
((0 . "LINE") (100 . "AcDbEntity") (8 . "ARCH") (62 . 7) (370 . 13) (100 . "AcDbLine") (10 9604.07239819 7454.7511312217
0.0) (11 9604.07239819 6900.4524886878 0.0))
((0 . "LINE") (100 . "AcDbEntity") (8 . "ARCH") (62 . 7) (370 . 13) (100 . "AcDbLine") (10 9604.07239819 6900.4524886878
0.0) (11 9151.5837104072 6900.4524886878 0.0))
((0 . "LINE") (100 . "AcDbEntity") (8 . "ARCH") (62 . 7) (370 . 13) (100 . "AcDbLine") (10 9151.5837104072
6900.4524886878 0.0) (11 9151.5837104072 7454.7511312217 0.0))
((0 . "LINE") (100 . "AcDbEntity") (8 . "ARCH") (62 . 7) (370 . 13) (100 . "AcDbLine") (10 9185.520361991 7420.814479638
0.0) (11 9570.1357466063 7420.814479638 0.0))
((0 . "LINE") (100 . "AcDbEntity") (8 . "ARCH") (62 . 7) (370 . 13) (100 . "AcDbLine") (10 9570.1357466063
7420.814479638 0.0) (11 9570.1357466063 6934.3891402715 0.0))
((0 . "LINE") (100 . "AcDbEntity") (8 . "ARCH") (62 . 7) (370 . 13) (100 . "AcDbLine") (10 9570.1357466063
6934.3891402715 0.0) (11 9185.520361991 6934.3891402715 0.0))
((0 . "LINE") (100 . "AcDbEntity") (8 . "ARCH") (62 . 7) (370 . 13) (100 . "AcDbLine") (10 9185.520361991
6934.3891402715 0.0) (11 9185.520361991 7420.814479638 0.0))
((0 . "LINE") (100 . "AcDbEntity") (8 . "ARCH") (62 . 7) (370 . 13) (100 . "AcDbLine") (10 9106.334841629
6855.2036199095 0.0) (11 9649.3212669683 6855.2036199095 0.0))
((0 . "LINE") (100 . "AcDbEntity") (8 . "ARCH") (62 . 7) (370 . 13) (100 . "AcDbLine") (10 9649.3212669683
6855.2036199095 0.0) (11 9649.3212669683 6809.9547511312 0.0))
((0 . "LINE") (100 . "AcDbEntity") (8 . "ARCH") (62 . 7) (370 . 13) (100 . "AcDbLine") (10 9106.334841629
6549.7737556561 0.0) (11 9106.334841629 6607.2624434389 0.0))
((0 . "LINE") (100 . "AcDbEntity") (8 . "ARCH") (62 . 7) (370 . 13) (100 . "AcDbLine") (10 9106.334841629
6607.2624434389 0.0) (11 9106.334841629 6643.0995475113 0.0))
((0 . "LINE") (100 . "AcDbEntity") (8 . "ARCH") (62 . 7) (370 . 13) (100 . "AcDbLine") (10 9106.334841629
6643.0995475113 0.0) (11 9106.334841629 6710.6787330317 0.0))
((0 . "LINE") (100 . "AcDbEntity") (8 . "ARCH") (62 . 7) (370 . 13) (100 . "AcDbLine") (10 9106.334841629
6710.6787330317 0.0) (11 9106.334841629 6762.4547511312 0.0))
((0 . "LINE") (100 . "AcDbEntity") (8 . "ARCH") (62 . 7) (370 . 13) (100 . "AcDbLine") (10 9106.334841629
6762.4547511312 0.0) (11 9106.334841629 6855.2036199095 0.0))
((0 . "LINE") (100 . "AcDbEntity") (8 . "ARCH") (62 . 7) (370 . 13) (100 . "AcDbLine") (10 10316.742081448
7647.0588235294 0.0) (11 11085.9728506787 7647.0588235294 0.0))
((0 . "LINE") (100 . "AcDbEntity") (8 . "ARCH") (62 . 7) (370 . 13) (100 . "AcDbLine") (10 11085.9728506787
7647.0588235294 0.0) (11 11085.9728506787 7635.7466063348 0.0))
((0 . "LINE") (100 . "AcDbEntity") (8 . "ARCH") (62 . 7) (370 . 13) (100 . "AcDbLine") (10 11085.9728506787
7635.7466063348 0.0) (11 11085.9728506787 7567.8733031674 0.0))
((0 . "LINE") (100 . "AcDbEntity") (8 . "ARCH") (62 . 7) (370 . 13) (100 . "AcDbLine") (10 11085.9728506787
7567.8733031674 0.0) (11 11085.9728506787 6549.7737556561 0.0))
((0 . "LINE") (100 . "AcDbEntity") (8 . "ARCH") (62 . 7) (370 . 13) (100 . "AcDbLine") (10 10316.742081448
6809.9547511312 0.0) (11 10316.742081448 7567.8733031674 0.0))
((0 . "LINE") (100 . "AcDbEntity") (8 . "ARCH") (62 . 7) (370 . 13) (100 . "AcDbLine") (10 10316.742081448
7567.8733031674 0.0) (11 10316.742081448 7635.7466063348 0.0))
((0 . "LINE") (100 . "AcDbEntity") (8 . "ARCH") (62 . 7) (370 . 13) (100 . "AcDbLine") (10 10316.742081448
7635.7466063348 0.0) (11 10316.742081448 7647.0588235294 0.0))
((0 . "LINE") (100 . "AcDbEntity") (8 . "ARCH") (62 . 7) (370 . 13) (100 . "AcDbLine") (10 10373.3031674208
7601.8099547511 0.0) (11 11029.4117647059 7601.8099547511 0.0))
((0 . "LINE") (100 . "AcDbEntity") (8 . "ARCH") (62 . 7) (370 . 13) (100 . "AcDbLine") (10 11029.4117647059
7601.8099547511 0.0) (11 11029.4117647059 6549.7737556561 0.0))
((0 . "LINE") (100 . "AcDbEntity") (8 . "ARCH") (62 . 7) (370 . 13) (100 . "AcDbLine") (10 10373.3031674208
6809.9547511312 0.0) (11 10373.3031674208 7601.8099547511 0.0))
((0 . "LINE") (100 . "AcDbEntity") (8 . "ARCH") (62 . 7) (370 . 13) (100 . "AcDbLine") (10 10475.1131221719 7500 0.0)
(11 10927.6018099548 7500 0.0))
((0 . "LINE") (100 . "AcDbEntity") (8 . "ARCH") (62 . 7) (370 . 13) (100 . "AcDbLine") (10 10927.6018099548 7500 0.0)
(11 10927.6018099548 6866.5158371041 0.0))
((0 . "LINE") (100 . "AcDbEntity") (8 . "ARCH") (62 . 7) (370 . 13) (100 . "AcDbLine") (10 10927.6018099548
6866.5158371041 0.0) (11 10475.1131221719 6866.5158371041 0.0))
((0 . "LINE") (100 . "AcDbEntity") (8 . "ARCH") (62 . 7) (370 . 13) (100 . "AcDbLine") (10 10475.1131221719
6866.5158371041 0.0) (11 10475.1131221719 7500 0.0))
((0 . "LINE") (100 . "AcDbEntity") (8 . "ARCH") (62 . 7) (370 . 13) (100 . "AcDbLine") (10 10520.3619909502
7454.7511312217 0.0) (11 10882.3529411765 7454.7511312217 0.0))
((0 . "LINE") (100 . "AcDbEntity") (8 . "ARCH") (62 . 7) (370 . 13) (100 . "AcDbLine") (10 10882.3529411765
7454.7511312217 0.0) (11 10882.3529411765 6900.4524886878 0.0))
((0 . "LINE") (100 . "AcDbEntity") (8 . "ARCH") (62 . 7) (370 . 13) (100 . "AcDbLine") (10 10882.3529411765
6900.4524886878 0.0) (11 10520.3619909502 6900.4524886878 0.0))
((0 . "LINE") (100 . "AcDbEntity") (8 . "ARCH") (62 . 7) (370 . 13) (100 . "AcDbLine") (10 10520.3619909502
6900.4524886878 0.0) (11 10520.3619909502 7454.7511312217 0.0))
((0 . "LINE") (100 . "AcDbEntity") (8 . "ARCH") (62 . 7) (370 . 13) (100 . "AcDbLine") (10 10554.2986425339
7420.814479638 0.0) (11 10848.4162895928 7420.814479638 0.0))
((0 . "LINE") (100 . "AcDbEntity") (8 . "ARCH") (62 . 7) (370 . 13) (100 . "AcDbLine") (10 10848.4162895928
7420.814479638 0.0) (11 10848.4162895928 6934.3891402715 0.0))
((0 . "LINE") (100 . "AcDbEntity") (8 . "ARCH") (62 . 7) (370 . 13) (100 . "AcDbLine") (10 10848.4162895928
6934.3891402715 0.0) (11 10554.2986425339 6934.3891402715 0.0))
((0 . "LINE") (100 . "AcDbEntity") (8 . "ARCH") (62 . 7) (370 . 13) (100 . "AcDbLine") (10 10554.2986425339
6934.3891402715 0.0) (11 10554.2986425339 7420.814479638 0.0))
((0 . "LINE") (100 . "AcDbEntity") (8 . "ARCH") (62 . 7) (370 . 13) (100 . "AcDbLine") (10 10475.1131221719
6855.2036199095 0.0) (11 10927.6018099548 6855.2036199095 0.0))
((0 . "LINE") (100 . "AcDbEntity") (8 . "ARCH") (62 . 7) (370 . 13) (100 . "AcDbLine") (10 10927.6018099548
6855.2036199095 0.0) (11 10927.6018099548 6761.8212669683 0.0))
((0 . "LINE") (100 . "AcDbEntity") (8 . "ARCH") (62 . 7) (370 . 13) (100 . "AcDbLine") (10 10927.6018099548
6761.8212669683 0.0) (11 10927.6018099548 6717.7488687783 0.0))
((0 . "LINE") (100 . "AcDbEntity") (8 . "ARCH") (62 . 7) (370 . 13) (100 . "AcDbLine") (10 10927.6018099548
6717.7488687783 0.0) (11 10927.6018099548 6687.9524886878 0.0))
((0 . "LINE") (100 . "AcDbEntity") (8 . "ARCH") (62 . 7) (370 . 13) (100 . "AcDbLine") (10 10927.6018099548
6687.9524886878 0.0) (11 10927.6018099548 6641.3122171946 0.0))
((0 . "LINE") (100 . "AcDbEntity") (8 . "ARCH") (62 . 7) (370 . 13) (100 . "AcDbLine") (10 10927.6018099548
6641.3122171946 0.0) (11 10927.6018099548 6607.0701357466 0.0))
((0 . "LINE") (100 . "AcDbEntity") (8 . "ARCH") (62 . 7) (370 . 13) (100 . "AcDbLine") (10 10927.6018099548
6607.0701357466 0.0) (11 10927.6018099548 6549.7737556561 0.0))
((0 . "LINE") (100 . "AcDbEntity") (8 . "ARCH") (62 . 7) (370 . 13) (100 . "AcDbLine") (10 10475.1131221719
6809.9547511312 0.0) (11 10475.1131221719 6855.2036199095 0.0))
((0 . "LINE") (100 . "AcDbEntity") (8 . "ARCH") (62 . 7) (370 . 13) (100 . "AcDbLine") (10 4004.5248868778
5916.2895927602 0.0) (11 4208.1447963801 6052.036199095 0.0))
((0 . "LINE") (100 . "AcDbEntity") (8 . "ARCH") (62 . 7) (370 . 13) (100 . "AcDbLine") (10 4208.1447963801
6052.036199095 0.0) (11 6606.334841629 6052.036199095 0.0))
((0 . "LINE") (100 . "AcDbEntity") (8 . "ARCH") (62 . 7) (370 . 13) (100 . "AcDbLine") (10 6606.334841629 6052.036199095
0.0) (11 6843.8914027149 5916.2895927602 0.0))
((0 . "LINE") (100 . "AcDbEntity") (8 . "ARCH") (62 . 7) (370 . 13) (100 . "AcDbLine") (10 4004.5248868778
5916.2895927602 0.0) (11 6843.8914027149 5916.2895927602 0.0))
((0 . "LINE") (100 . "AcDbEntity") (8 . "ARCH") (62 . 7) (370 . 13) (100 . "AcDbLine") (10 6843.8914027149
5916.2895927602 0.0) (11 6843.8914027149 5848.4162895928 0.0))
((0 . "LINE") (100 . "AcDbEntity") (8 . "ARCH") (62 . 7) (370 . 13) (100 . "AcDbLine") (10 6843.8914027149
5848.4162895928 0.0) (11 4004.5248868778 5848.4162895928 0.0))
((0 . "LINE") (100 . "AcDbEntity") (8 . "ARCH") (62 . 7) (370 . 13) (100 . "AcDbLine") (10 4004.5248868778
5848.4162895928 0.0) (11 4004.5248868778 5916.2895927602 0.0))
((0 . "LINE") (100 . "AcDbEntity") (8 . "ARCH") (62 . 7) (370 . 13) (100 . "AcDbLine") (10 4004.5248868778
5848.4162895928 0.0) (11 4004.5248868778 5814.4796380091 0.0))
((0 . "LINE") (100 . "AcDbEntity") (8 . "ARCH") (62 . 7) (370 . 13) (100 . "AcDbLine") (10 4004.5248868778
5814.4796380091 0.0) (11 4004.5248868778 5791.8552036199 0.0))
((0 . "LINE") (100 . "AcDbEntity") (8 . "ARCH") (62 . 7) (370 . 13) (100 . "AcDbLine") (10 4004.5248868778
5791.8552036199 0.0) (11 4083.7104072398 5757.9185520362 0.0))
((0 . "LINE") (100 . "AcDbEntity") (8 . "ARCH") (62 . 7) (370 . 13) (100 . "AcDbLine") (10 4083.7104072398
5757.9185520362 0.0) (11 6753.3936651584 5757.9185520362 0.0))
((0 . "LINE") (100 . "AcDbEntity") (8 . "ARCH") (62 . 7) (370 . 13) (100 . "AcDbLine") (10 6753.3936651584
5757.9185520362 0.0) (11 6843.8914027149 5791.8552036199 0.0))
((0 . "LINE") (100 . "AcDbEntity") (8 . "ARCH") (62 . 7) (370 . 13) (100 . "AcDbLine") (10 6843.8914027149
5791.8552036199 0.0) (11 6843.8914027149 5814.4796380091 0.0))
((0 . "LINE") (100 . "AcDbEntity") (8 . "ARCH") (62 . 7) (370 . 13) (100 . "AcDbLine") (10 6843.8914027149
5814.4796380091 0.0) (11 6843.8914027149 5848.4162895928 0.0))
((0 . "LINE") (100 . "AcDbEntity") (8 . "ARCH") (62 . 7) (370 . 13) (100 . "AcDbLine") (10 4038.4615384615
5757.9185520362 0.0) (11 4083.7104072398 5757.9185520362 0.0))
((0 . "LINE") (100 . "AcDbEntity") (8 . "ARCH") (62 . 7) (370 . 13) (100 . "AcDbLine") (10 6753.3936651584
5757.9185520362 0.0) (11 6787.3303167421 5757.9185520362 0.0))
((0 . "LINE") (100 . "AcDbEntity") (8 . "ARCH") (62 . 7) (370 . 13) (100 . "AcDbLine") (10 6787.3303167421
5757.9185520362 0.0) (11 6787.3303167421 5746.6063348416 0.0))
((0 . "LINE") (100 . "AcDbEntity") (8 . "ARCH") (62 . 7) (370 . 13) (100 . "AcDbLine") (10 6787.3303167421
5746.6063348416 0.0) (11 6787.3303167421 5701.3574660633 0.0))
((0 . "LINE") (100 . "AcDbEntity") (8 . "ARCH") (62 . 7) (370 . 13) (100 . "AcDbLine") (10 6787.3303167421
5701.3574660633 0.0) (11 6708.1447963801 5701.3574660633 0.0))
((0 . "LINE") (100 . "AcDbEntity") (8 . "ARCH") (62 . 7) (370 . 13) (100 . "AcDbLine") (10 6708.1447963801
5701.3574660633 0.0) (11 4140.2714932127 5701.3574660633 0.0))
((0 . "LINE") (100 . "AcDbEntity") (8 . "ARCH") (62 . 7) (370 . 13) (100 . "AcDbLine") (10 4140.2714932127
5701.3574660633 0.0) (11 4038.4615384615 5701.3574660633 0.0))
((0 . "LINE") (100 . "AcDbEntity") (8 . "ARCH") (62 . 7) (370 . 13) (100 . "AcDbLine") (10 4038.4615384615
5701.3574660633 0.0) (11 4038.4615384615 5746.6063348416 0.0))
((0 . "LINE") (100 . "AcDbEntity") (8 . "ARCH") (62 . 7) (370 . 13) (100 . "AcDbLine") (10 4038.4615384615
5746.6063348416 0.0) (11 4038.4615384615 5757.9185520362 0.0))
((0 . "LINE") (100 . "AcDbEntity") (8 . "ARCH") (62 . 7) (370 . 13) (100 . "AcDbLine") (10 6708.1447963801
5701.3574660633 0.0) (11 6708.1447963801 5656.1085972851 0.0))
((0 . "LINE") (100 . "AcDbEntity") (8 . "ARCH") (62 . 7) (370 . 13) (100 . "AcDbLine") (10 6708.1447963801
5656.1085972851 0.0) (11 6674.2081447964 5622.1719457014 0.0))
((0 . "LINE") (100 . "AcDbEntity") (8 . "ARCH") (62 . 7) (370 . 13) (100 . "AcDbLine") (10 6674.2081447964
5622.1719457014 0.0) (11 6674.2081447964 5588.2352941176 0.0))
((0 . "LINE") (100 . "AcDbEntity") (8 . "ARCH") (62 . 7) (370 . 13) (100 . "AcDbLine") (10 6674.2081447964
5588.2352941176 0.0) (11 6674.2081447964 5576.9230769231 0.0))
((0 . "LINE") (100 . "AcDbEntity") (8 . "ARCH") (62 . 7) (370 . 13) (100 . "AcDbLine") (10 6674.2081447964
5576.9230769231 0.0) (11 4162.8959276018 5576.9230769231 0.0))
((0 . "LINE") (100 . "AcDbEntity") (8 . "ARCH") (62 . 7) (370 . 13) (100 . "AcDbLine") (10 4162.8959276018
5576.9230769231 0.0) (11 4162.8959276018 5588.2352941176 0.0))
((0 . "LINE") (100 . "AcDbEntity") (8 . "ARCH") (62 . 7) (370 . 13) (100 . "AcDbLine") (10 4162.8959276018
5588.2352941176 0.0) (11 4162.8959276018 5610.8597285068 0.0))
((0 . "LINE") (100 . "AcDbEntity") (8 . "ARCH") (62 . 7) (370 . 13) (100 . "AcDbLine") (10 4162.8959276018
5610.8597285068 0.0) (11 4162.8959276018 5622.1719457014 0.0))
((0 . "LINE") (100 . "AcDbEntity") (8 . "ARCH") (62 . 7) (370 . 13) (100 . "AcDbLine") (10 4162.8959276018
5622.1719457014 0.0) (11 4140.2714932127 5656.1085972851 0.0))
((0 . "LINE") (100 . "AcDbEntity") (8 . "ARCH") (62 . 7) (370 . 13) (100 . "AcDbLine") (10 4140.2714932127
5656.1085972851 0.0) (11 4140.2714932127 5701.3574660633 0.0))
((0 . "LINE") (100 . "AcDbEntity") (8 . "LOUVERS") (62 . 7) (370 . 13) (100 . "AcDbLine") (10 4174.2081447964
5531.6742081448 0.0) (11 4233.0656108597 5531.6742081448 0.0))
((0 . "LINE") (100 . "AcDbEntity") (8 . "LOUVERS") (62 . 7) (370 . 13) (100 . "AcDbLine") (10 4233.0656108597
5531.6742081448 0.0) (11 4252.1719457014 5531.6742081448 0.0))
((0 . "LINE") (100 . "AcDbEntity") (8 . "LOUVERS") (62 . 7) (370 . 13) (100 . "AcDbLine") (10 4252.1719457014
5531.6742081448 0.0) (11 4310.9502262443 5531.6742081448 0.0))
((0 . "LINE") (100 . "AcDbEntity") (8 . "LOUVERS") (62 . 7) (370 . 13) (100 . "AcDbLine") (10 4310.9502262443
5531.6742081448 0.0) (11 4331.0859728507 5531.6742081448 0.0))
((0 . "LINE") (100 . "AcDbEntity") (8 . "LOUVERS") (62 . 7) (370 . 13) (100 . "AcDbLine") (10 4331.0859728507
5531.6742081448 0.0) (11 4392.8959276018 5531.6742081448 0.0))
((0 . "LINE") (100 . "AcDbEntity") (8 . "LOUVERS") (62 . 7) (370 . 13) (100 . "AcDbLine") (10 4392.8959276018
5531.6742081448 0.0) (11 4460.6221719457 5531.6742081448 0.0))
((0 . "LINE") (100 . "AcDbEntity") (8 . "LOUVERS") (62 . 7) (370 . 13) (100 . "AcDbLine") (10 4460.6221719457
5531.6742081448 0.0) (11 4499.0384615385 5531.6742081448 0.0))
((0 . "LINE") (100 . "AcDbEntity") (8 . "LOUVERS") (62 . 7) (370 . 13) (100 . "AcDbLine") (10 4499.0384615385
5531.6742081448 0.0) (11 4578.9592760181 5531.6742081448 0.0))
((0 . "LINE") (100 . "AcDbEntity") (8 . "LOUVERS") (62 . 7) (370 . 13) (100 . "AcDbLine") (10 4578.9592760181
5531.6742081448 0.0) (11 4640.7918552036 5531.6742081448 0.0))
((0 . "LINE") (100 . "AcDbEntity") (8 . "LOUVERS") (62 . 7) (370 . 13) (100 . "AcDbLine") (10 4640.7918552036
5531.6742081448 0.0) (11 4671.9457013575 5531.6742081448 0.0))
((0 . "LINE") (100 . "AcDbEntity") (8 . "ARCH") (62 . 7) (370 . 13) (100 . "AcDbLine") (10 4671.9457013575
5531.6742081448 0.0) (11 6210.407239819 5531.6742081448 0.0))
((0 . "LINE") (100 . "AcDbEntity") (8 . "ARCH") (62 . 7) (370 . 13) (100 . "AcDbLine") (10 6210.407239819
5531.6742081448 0.0) (11 6234.2647058824 5531.6742081448 0.0))
((0 . "LINE") (100 . "AcDbEntity") (8 . "ARCH") (62 . 7) (370 . 13) (100 . "AcDbLine") (10 6234.2647058824
5531.6742081448 0.0) (11 6294.2194570136 5531.6742081448 0.0))
((0 . "LINE") (100 . "AcDbEntity") (8 . "ARCH") (62 . 7) (370 . 13) (100 . "AcDbLine") (10 6294.2194570136
5531.6742081448 0.0) (11 6374.4230769231 5531.6742081448 0.0))
((0 . "LINE") (100 . "AcDbEntity") (8 . "ARCH") (62 . 7) (370 . 13) (100 . "AcDbLine") (10 6374.4230769231
5531.6742081448 0.0) (11 6454.7737556561 5531.6742081448 0.0))
((0 . "LINE") (100 . "AcDbEntity") (8 . "ARCH") (62 . 7) (370 . 13) (100 . "AcDbLine") (10 6454.7737556561
5531.6742081448 0.0) (11 6508.2918552036 5531.6742081448 0.0))
((0 . "LINE") (100 . "AcDbEntity") (8 . "ARCH") (62 . 7) (370 . 13) (100 . "AcDbLine") (10 6508.2918552036
5531.6742081448 0.0) (11 6523.9932126697 5531.6742081448 0.0))
((0 . "LINE") (100 . "AcDbEntity") (8 . "ARCH") (62 . 7) (370 . 13) (100 . "AcDbLine") (10 6523.9932126697
5531.6742081448 0.0) (11 6582.5113122172 5531.6742081448 0.0))
((0 . "LINE") (100 . "AcDbEntity") (8 . "ARCH") (62 . 7) (370 . 13) (100 . "AcDbLine") (10 6582.5113122172
5531.6742081448 0.0) (11 6658.6312217195 5531.6742081448 0.0))
((0 . "LINE") (100 . "AcDbEntity") (8 . "ARCH") (62 . 7) (370 . 13) (100 . "AcDbLine") (10 6658.6312217195
5531.6742081448 0.0) (11 6674.2081447964 5531.6742081448 0.0))
((0 . "LINE") (100 . "AcDbEntity") (8 . "ARCH") (62 . 7) (370 . 13) (100 . "AcDbLine") (10 4162.8959276018
5588.2352941176 0.0) (11 6674.2081447964 5588.2352941176 0.0))
((0 . "LINE") (100 . "AcDbEntity") (8 . "ARCH") (62 . 7) (370 . 13) (100 . "AcDbLine") (10 6674.2081447964
5588.2352941176 0.0) (11 6685.520361991 5588.2352941176 0.0))
((0 . "LINE") (100 . "AcDbEntity") (8 . "ARCH") (62 . 7) (370 . 13) (100 . "AcDbLine") (10 4038.4615384615
3778.2805429864 0.0) (11 6787.3303167421 3778.2805429864 0.0))
((0 . "LINE") (100 . "AcDbEntity") (8 . "ARCH") (62 . 7) (370 . 13) (100 . "AcDbLine") (10 6787.3303167421
3778.2805429864 0.0) (11 6787.3303167421 3721.7194570136 0.0))
((0 . "LINE") (100 . "AcDbEntity") (8 . "ARCH") (62 . 7) (370 . 13) (100 . "AcDbLine") (10 6787.3303167421
3721.7194570136 0.0) (11 6787.3303167421 3585.9728506787 0.0))
((0 . "LINE") (100 . "AcDbEntity") (8 . "ARCH") (62 . 7) (370 . 13) (100 . "AcDbLine") (10 6787.3303167421
3585.9728506787 0.0) (11 6787.3303167421 3235.2941176471 0.0))
((0 . "LINE") (100 . "AcDbEntity") (8 . "ARCH") (62 . 7) (370 . 13) (100 . "AcDbLine") (10 6787.3303167421
3235.2941176471 0.0) (11 6776.0180995475 3235.2941176471 0.0))
((0 . "LINE") (100 . "AcDbEntity") (8 . "ARCH") (62 . 7) (370 . 13) (100 . "AcDbLine") (10 6776.0180995475
3235.2941176471 0.0) (11 4049.7737556561 3235.2941176471 0.0))
((0 . "LINE") (100 . "AcDbEntity") (8 . "ARCH") (62 . 7) (370 . 13) (100 . "AcDbLine") (10 4049.7737556561
3235.2941176471 0.0) (11 4038.4615384615 3235.2941176471 0.0))
((0 . "LINE") (100 . "AcDbEntity") (8 . "ARCH") (62 . 7) (370 . 13) (100 . "AcDbLine") (10 4038.4615384615
3235.2941176471 0.0) (11 4038.4615384615 3585.9728506787 0.0))
((0 . "LINE") (100 . "AcDbEntity") (8 . "ARCH") (62 . 7) (370 . 13) (100 . "AcDbLine") (10 4038.4615384615
3585.9728506787 0.0) (11 4038.4615384615 3721.7194570136 0.0))
((0 . "LINE") (100 . "AcDbEntity") (8 . "ARCH") (62 . 7) (370 . 13) (100 . "AcDbLine") (10 4038.4615384615
3721.7194570136 0.0) (11 4038.4615384615 3778.2805429864 0.0))
((0 . "LINE") (100 . "AcDbEntity") (8 . "ARCH") (62 . 7) (370 . 13) (100 . "AcDbLine") (10 6776.0180995475
3235.2941176471 0.0) (11 6776.0180995475 2941.1764705882 0.0))
((0 . "LINE") (100 . "AcDbEntity") (8 . "ARCH") (62 . 7) (370 . 13) (100 . "AcDbLine") (10 6776.0180995475
2941.1764705882 0.0) (11 4049.7737556561 2941.1764705882 0.0))
((0 . "LINE") (100 . "AcDbEntity") (8 . "ARCH") (62 . 7) (370 . 13) (100 . "AcDbLine") (10 4049.7737556561
2941.1764705882 0.0) (11 4049.7737556561 3235.2941176471 0.0))
((0 . "LINE") (100 . "AcDbEntity") (8 . "ARCH") (62 . 7) (370 . 13) (100 . "AcDbLine") (10 4027.149321267
2941.1764705882 0.0) (11 4049.7737556561 2941.1764705882 0.0))
((0 . "LINE") (100 . "AcDbEntity") (8 . "ARCH") (62 . 7) (370 . 13) (100 . "AcDbLine") (10 6776.0180995475
2941.1764705882 0.0) (11 6787.3303167421 2941.1764705882 0.0))
((0 . "LINE") (100 . "AcDbEntity") (8 . "ARCH") (62 . 7) (370 . 13) (100 . "AcDbLine") (10 6787.3303167421
2941.1764705882 0.0) (11 6787.3303167421 2861.9909502262 0.0))
((0 . "LINE") (100 . "AcDbEntity") (8 . "ARCH") (62 . 7) (370 . 13) (100 . "AcDbLine") (10 6787.3303167421
2861.9909502262 0.0) (11 6764.7058823529 2861.9909502262 0.0))
((0 . "LINE") (100 . "AcDbEntity") (8 . "ARCH") (62 . 7) (370 . 13) (100 . "AcDbLine") (10 6764.7058823529
2861.9909502262 0.0) (11 4049.7737556561 2861.9909502262 0.0))
((0 . "LINE") (100 . "AcDbEntity") (8 . "ARCH") (62 . 7) (370 . 13) (100 . "AcDbLine") (10 4049.7737556561
2861.9909502262 0.0) (11 4027.149321267 2861.9909502262 0.0))
((0 . "LINE") (100 . "AcDbEntity") (8 . "ARCH") (62 . 7) (370 . 13) (100 . "AcDbLine") (10 4027.149321267
2861.9909502262 0.0) (11 4027.149321267 2941.1764705882 0.0))
((0 . "LINE") (100 . "AcDbEntity") (8 . "ARCH") (62 . 7) (370 . 13) (100 . "AcDbLine") (10 4049.7737556561
2861.9909502262 0.0) (11 4117.6470588235 2794.1176470588 0.0))
((0 . "LINE") (100 . "AcDbEntity") (8 . "ARCH") (62 . 7) (370 . 13) (100 . "AcDbLine") (10 4117.6470588235
2794.1176470588 0.0) (11 4128.9592760181 2748.8687782805 0.0))
((0 . "LINE") (100 . "AcDbEntity") (8 . "ARCH") (62 . 7) (370 . 13) (100 . "AcDbLine") (10 4128.9592760181
2748.8687782805 0.0) (11 4140.2714932127 2703.6199095023 0.0))
((0 . "LINE") (100 . "AcDbEntity") (8 . "ARCH") (62 . 7) (370 . 13) (100 . "AcDbLine") (10 4140.2714932127
2703.6199095023 0.0) (11 6685.520361991 2703.6199095023 0.0))
((0 . "LINE") (100 . "AcDbEntity") (8 . "ARCH") (62 . 7) (370 . 13) (100 . "AcDbLine") (10 6685.520361991
2703.6199095023 0.0) (11 6696.8325791855 2748.8687782805 0.0))
((0 . "LINE") (100 . "AcDbEntity") (8 . "ARCH") (62 . 7) (370 . 13) (100 . "AcDbLine") (10 6696.8325791855
2748.8687782805 0.0) (11 6708.1447963801 2794.1176470588 0.0))
((0 . "LINE") (100 . "AcDbEntity") (8 . "ARCH") (62 . 7) (370 . 13) (100 . "AcDbLine") (10 6708.1447963801
2794.1176470588 0.0) (11 6764.7058823529 2861.9909502262 0.0))
((0 . "LINE") (100 . "AcDbEntity") (8 . "ARCH") (62 . 7) (370 . 13) (100 . "AcDbLine") (10 4128.9592760181
2748.8687782805 0.0) (11 6696.8325791855 2748.8687782805 0.0))
((0 . "LINE") (100 . "AcDbEntity") (8 . "ARCH") (62 . 7) (370 . 13) (100 . "AcDbLine") (10 4140.2714932127
938.9140271493 0.0) (11 6719.4570135747 938.9140271493 0.0))
((0 . "LINE") (100 . "AcDbEntity") (8 . "ARCH") (62 . 7) (370 . 13) (100 . "AcDbLine") (10 6719.4570135747
938.9140271493 0.0) (11 6719.4570135747 859.7285067873 0.0))
((0 . "LINE") (100 . "AcDbEntity") (8 . "ARCH") (62 . 7) (370 . 13) (100 . "AcDbLine") (10 6719.4570135747
859.7285067873 0.0) (11 6651.5837104072 859.7285067873 0.0))
((0 . "LINE") (100 . "AcDbEntity") (8 . "ARCH") (62 . 7) (370 . 13) (100 . "AcDbLine") (10 6651.5837104072
859.7285067873 0.0) (11 4208.1447963801 859.7285067873 0.0))
((0 . "LINE") (100 . "AcDbEntity") (8 . "ARCH") (62 . 7) (370 . 13) (100 . "AcDbLine") (10 4208.1447963801
859.7285067873 0.0) (11 4140.2714932127 859.7285067873 0.0))
((0 . "LINE") (100 . "AcDbEntity") (8 . "ARCH") (62 . 7) (370 . 13) (100 . "AcDbLine") (10 4140.2714932127
859.7285067873 0.0) (11 4140.2714932127 938.9140271493 0.0))
((0 . "LINE") (100 . "AcDbEntity") (8 . "ARCH") (62 . 7) (370 . 13) (100 . "AcDbLine") (10 6651.5837104072
859.7285067873 0.0) (11 6651.5837104072 599.5475113122 0.0))
((0 . "LINE") (100 . "AcDbEntity") (8 . "ARCH") (62 . 7) (370 . 13) (100 . "AcDbLine") (10 6651.5837104072
599.5475113122 0.0) (11 4208.1447963801 599.5475113122 0.0))
((0 . "LINE") (100 . "AcDbEntity") (8 . "ARCH") (62 . 7) (370 . 13) (100 . "AcDbLine") (10 4208.1447963801
599.5475113122 0.0) (11 4208.1447963801 859.7285067873 0.0))
((0 . "LINE") (100 . "AcDbEntity") (8 . "ARCH") (62 . 7) (370 . 13) (100 . "AcDbLine") (10 4208.1447963801
576.9230769231 0.0) (11 6651.5837104072 576.9230769231 0.0))
((0 . "LINE") (100 . "AcDbEntity") (8 . "ARCH") (62 . 7) (370 . 13) (100 . "AcDbLine") (10 3404.9773755656
3382.3529411765 0.0) (11 3529.4117647059 3382.3529411765 0.0))
((0 . "LINE") (100 . "AcDbEntity") (8 . "ARCH") (62 . 7) (370 . 13) (100 . "AcDbLine") (10 3529.4117647059
3382.3529411765 0.0) (11 3529.4117647059 2533.9366515837 0.0))
((0 . "LINE") (100 . "AcDbEntity") (8 . "ARCH") (62 . 7) (370 . 13) (100 . "AcDbLine") (10 3529.4117647059
2533.9366515837 0.0) (11 3404.9773755656 2533.9366515837 0.0))
((0 . "LINE") (100 . "AcDbEntity") (8 . "ARCH") (62 . 7) (370 . 13) (100 . "AcDbLine") (10 3404.9773755656
2533.9366515837 0.0) (11 3404.9773755656 3382.3529411765 0.0))
((0 . "LINE") (100 . "AcDbEntity") (8 . "ARCH") (62 . 7) (370 . 13) (100 . "AcDbLine") (10 3438.9140271493
3337.1040723982 0.0) (11 3495.4751131222 3337.1040723982 0.0))
((0 . "LINE") (100 . "AcDbEntity") (8 . "ARCH") (62 . 7) (370 . 13) (100 . "AcDbLine") (10 3495.4751131222
3337.1040723982 0.0) (11 3495.4751131222 2590.4977375566 0.0))
((0 . "LINE") (100 . "AcDbEntity") (8 . "ARCH") (62 . 7) (370 . 13) (100 . "AcDbLine") (10 3495.4751131222
2590.4977375566 0.0) (11 3438.9140271493 2590.4977375566 0.0))
((0 . "LINE") (100 . "AcDbEntity") (8 . "ARCH") (62 . 7) (370 . 13) (100 . "AcDbLine") (10 3438.9140271493
2590.4977375566 0.0) (11 3438.9140271493 3337.1040723982 0.0))
((0 . "LINE") (100 . "AcDbEntity") (8 . "ARCH") (62 . 7) (370 . 13) (100 . "AcDbLine") (10 7273.7556561086
3382.3529411765 0.0) (11 7398.1900452489 3382.3529411765 0.0))
((0 . "LINE") (100 . "AcDbEntity") (8 . "ARCH") (62 . 7) (370 . 13) (100 . "AcDbLine") (10 7398.1900452489
3382.3529411765 0.0) (11 7398.1900452489 2533.9366515837 0.0))
((0 . "LINE") (100 . "AcDbEntity") (8 . "ARCH") (62 . 7) (370 . 13) (100 . "AcDbLine") (10 7398.1900452489
2533.9366515837 0.0) (11 7273.7556561086 2533.9366515837 0.0))
((0 . "LINE") (100 . "AcDbEntity") (8 . "ARCH") (62 . 7) (370 . 13) (100 . "AcDbLine") (10 7273.7556561086
2533.9366515837 0.0) (11 7273.7556561086 3382.3529411765 0.0))
((0 . "LINE") (100 . "AcDbEntity") (8 . "ARCH") (62 . 7) (370 . 13) (100 . "AcDbLine") (10 7307.6923076923
3337.1040723982 0.0) (11 7364.2533936652 3337.1040723982 0.0))
((0 . "LINE") (100 . "AcDbEntity") (8 . "ARCH") (62 . 7) (370 . 13) (100 . "AcDbLine") (10 7364.2533936652
3337.1040723982 0.0) (11 7364.2533936652 2590.4977375566 0.0))
((0 . "LINE") (100 . "AcDbEntity") (8 . "ARCH") (62 . 7) (370 . 13) (100 . "AcDbLine") (10 7364.2533936652
2590.4977375566 0.0) (11 7307.6923076923 2590.4977375566 0.0))
((0 . "LINE") (100 . "AcDbEntity") (8 . "ARCH") (62 . 7) (370 . 13) (100 . "AcDbLine") (10 7307.6923076923
2590.4977375566 0.0) (11 7307.6923076923 3337.1040723982 0.0))
((0 . "LINE") (100 . "AcDbEntity") (8 . "ARCH") (62 . 7) (370 . 13) (100 . "AcDbLine") (10 13156.1085972851
5916.2895927602 0.0) (11 13359.7285067873 6052.036199095 0.0))
((0 . "LINE") (100 . "AcDbEntity") (8 . "ARCH") (62 . 7) (370 . 13) (100 . "AcDbLine") (10 13359.7285067873
6052.036199095 0.0) (11 15757.9185520362 6052.036199095 0.0))
((0 . "LINE") (100 . "AcDbEntity") (8 . "ARCH") (62 . 7) (370 . 13) (100 . "AcDbLine") (10 15757.9185520362
6052.036199095 0.0) (11 15995.4751131222 5916.2895927602 0.0))
((0 . "LINE") (100 . "AcDbEntity") (8 . "ARCH") (62 . 7) (370 . 13) (100 . "AcDbLine") (10 13156.1085972851
5916.2895927602 0.0) (11 15995.4751131222 5916.2895927602 0.0))
((0 . "LINE") (100 . "AcDbEntity") (8 . "ARCH") (62 . 7) (370 . 13) (100 . "AcDbLine") (10 15995.4751131222
5916.2895927602 0.0) (11 15995.4751131222 5848.4162895928 0.0))
((0 . "LINE") (100 . "AcDbEntity") (8 . "ARCH") (62 . 7) (370 . 13) (100 . "AcDbLine") (10 15995.4751131222
5848.4162895928 0.0) (11 13156.1085972851 5848.4162895928 0.0))
((0 . "LINE") (100 . "AcDbEntity") (8 . "ARCH") (62 . 7) (370 . 13) (100 . "AcDbLine") (10 13156.1085972851
5848.4162895928 0.0) (11 13156.1085972851 5916.2895927602 0.0))
((0 . "LINE") (100 . "AcDbEntity") (8 . "ARCH") (62 . 7) (370 . 13) (100 . "AcDbLine") (10 13156.1085972851
5848.4162895928 0.0) (11 13156.1085972851 5814.4796380091 0.0))
((0 . "LINE") (100 . "AcDbEntity") (8 . "ARCH") (62 . 7) (370 . 13) (100 . "AcDbLine") (10 13156.1085972851
5814.4796380091 0.0) (11 13156.1085972851 5791.8552036199 0.0))
((0 . "LINE") (100 . "AcDbEntity") (8 . "ARCH") (62 . 7) (370 . 13) (100 . "AcDbLine") (10 13156.1085972851
5791.8552036199 0.0) (11 13235.2941176471 5757.9185520362 0.0))
((0 . "LINE") (100 . "AcDbEntity") (8 . "ARCH") (62 . 7) (370 . 13) (100 . "AcDbLine") (10 13235.2941176471
5757.9185520362 0.0) (11 15904.9773755656 5757.9185520362 0.0))
((0 . "LINE") (100 . "AcDbEntity") (8 . "ARCH") (62 . 7) (370 . 13) (100 . "AcDbLine") (10 15904.9773755656
5757.9185520362 0.0) (11 15995.4751131222 5791.8552036199 0.0))
((0 . "LINE") (100 . "AcDbEntity") (8 . "ARCH") (62 . 7) (370 . 13) (100 . "AcDbLine") (10 15995.4751131222
5791.8552036199 0.0) (11 15995.4751131222 5814.4796380091 0.0))
((0 . "LINE") (100 . "AcDbEntity") (8 . "ARCH") (62 . 7) (370 . 13) (100 . "AcDbLine") (10 15995.4751131222
5814.4796380091 0.0) (11 15995.4751131222 5848.4162895928 0.0))
((0 . "LINE") (100 . "AcDbEntity") (8 . "ARCH") (62 . 7) (370 . 13) (100 . "AcDbLine") (10 13190.0452488688
5757.9185520362 0.0) (11 13235.2941176471 5757.9185520362 0.0))
((0 . "LINE") (100 . "AcDbEntity") (8 . "ARCH") (62 . 7) (370 . 13) (100 . "AcDbLine") (10 15904.9773755656
5757.9185520362 0.0) (11 15938.9140271493 5757.9185520362 0.0))
((0 . "LINE") (100 . "AcDbEntity") (8 . "ARCH") (62 . 7) (370 . 13) (100 . "AcDbLine") (10 15938.9140271493
5757.9185520362 0.0) (11 15938.9140271493 5746.6063348416 0.0))
((0 . "LINE") (100 . "AcDbEntity") (8 . "ARCH") (62 . 7) (370 . 13) (100 . "AcDbLine") (10 15938.9140271493
5746.6063348416 0.0) (11 15938.9140271493 5701.3574660633 0.0))
((0 . "LINE") (100 . "AcDbEntity") (8 . "ARCH") (62 . 7) (370 . 13) (100 . "AcDbLine") (10 15938.9140271493
5701.3574660633 0.0) (11 15859.7285067873 5701.3574660633 0.0))
((0 . "LINE") (100 . "AcDbEntity") (8 . "ARCH") (62 . 7) (370 . 13) (100 . "AcDbLine") (10 15859.7285067873
5701.3574660633 0.0) (11 13291.8552036199 5701.3574660633 0.0))
((0 . "LINE") (100 . "AcDbEntity") (8 . "ARCH") (62 . 7) (370 . 13) (100 . "AcDbLine") (10 13291.8552036199
5701.3574660633 0.0) (11 13190.0452488688 5701.3574660633 0.0))
((0 . "LINE") (100 . "AcDbEntity") (8 . "ARCH") (62 . 7) (370 . 13) (100 . "AcDbLine") (10 13190.0452488688
5701.3574660633 0.0) (11 13190.0452488688 5746.6063348416 0.0))
((0 . "LINE") (100 . "AcDbEntity") (8 . "ARCH") (62 . 7) (370 . 13) (100 . "AcDbLine") (10 13190.0452488688
5746.6063348416 0.0) (11 13190.0452488688 5757.9185520362 0.0))
((0 . "LINE") (100 . "AcDbEntity") (8 . "ARCH") (62 . 7) (370 . 13) (100 . "AcDbLine") (10 15859.7285067873
5701.3574660633 0.0) (11 15859.7285067873 5656.1085972851 0.0))
((0 . "LINE") (100 . "AcDbEntity") (8 . "ARCH") (62 . 7) (370 . 13) (100 . "AcDbLine") (10 15859.7285067873
5656.1085972851 0.0) (11 15825.7918552036 5622.1719457014 0.0))
((0 . "LINE") (100 . "AcDbEntity") (8 . "ARCH") (62 . 7) (370 . 13) (100 . "AcDbLine") (10 15825.7918552036
5622.1719457014 0.0) (11 15825.7918552036 5588.2352941176 0.0))
((0 . "LINE") (100 . "AcDbEntity") (8 . "ARCH") (62 . 7) (370 . 13) (100 . "AcDbLine") (10 15825.7918552036
5588.2352941176 0.0) (11 15825.7918552036 5576.9230769231 0.0))
((0 . "LINE") (100 . "AcDbEntity") (8 . "ARCH") (62 . 7) (370 . 13) (100 . "AcDbLine") (10 15825.7918552036
5576.9230769231 0.0) (11 13314.4796380091 5576.9230769231 0.0))
((0 . "LINE") (100 . "AcDbEntity") (8 . "ARCH") (62 . 7) (370 . 13) (100 . "AcDbLine") (10 13314.4796380091
5576.9230769231 0.0) (11 13314.4796380091 5588.2352941176 0.0))
((0 . "LINE") (100 . "AcDbEntity") (8 . "ARCH") (62 . 7) (370 . 13) (100 . "AcDbLine") (10 13314.4796380091
5588.2352941176 0.0) (11 13314.4796380091 5610.8597285068 0.0))
((0 . "LINE") (100 . "AcDbEntity") (8 . "ARCH") (62 . 7) (370 . 13) (100 . "AcDbLine") (10 13314.4796380091
5610.8597285068 0.0) (11 13314.4796380091 5622.1719457014 0.0))
((0 . "LINE") (100 . "AcDbEntity") (8 . "ARCH") (62 . 7) (370 . 13) (100 . "AcDbLine") (10 13314.4796380091
5622.1719457014 0.0) (11 13291.8552036199 5656.1085972851 0.0))
((0 . "LINE") (100 . "AcDbEntity") (8 . "ARCH") (62 . 7) (370 . 13) (100 . "AcDbLine") (10 13291.8552036199
5656.1085972851 0.0) (11 13291.8552036199 5701.3574660633 0.0))
((0 . "LINE") (100 . "AcDbEntity") (8 . "LOUVERS") (62 . 7) (370 . 13) (100 . "AcDbLine") (10 13325.7918552036
5531.6742081448 0.0) (11 13326.334841629 5531.6742081448 0.0))
((0 . "LINE") (100 . "AcDbEntity") (8 . "ARCH") (62 . 7) (370 . 13) (100 . "AcDbLine") (10 13326.334841629
5531.6742081448 0.0) (11 13386.9230769231 5531.6742081448 0.0))
((0 . "LINE") (100 . "AcDbEntity") (8 . "ARCH") (62 . 7) (370 . 13) (100 . "AcDbLine") (10 13386.9230769231
5531.6742081448 0.0) (11 13464.7850678733 5531.6742081448 0.0))
((0 . "LINE") (100 . "AcDbEntity") (8 . "ARCH") (62 . 7) (370 . 13) (100 . "AcDbLine") (10 13464.7850678733
5531.6742081448 0.0) (11 13480.4524886878 5531.6742081448 0.0))
((0 . "LINE") (100 . "AcDbEntity") (8 . "ARCH") (62 . 7) (370 . 13) (100 . "AcDbLine") (10 13480.4524886878
5531.6742081448 0.0) (11 13543.5520361991 5531.6742081448 0.0))
((0 . "LINE") (100 . "AcDbEntity") (8 . "ARCH") (62 . 7) (370 . 13) (100 . "AcDbLine") (10 13543.5520361991
5531.6742081448 0.0) (11 13625.4524886878 5531.6742081448 0.0))
((0 . "LINE") (100 . "AcDbEntity") (8 . "ARCH") (62 . 7) (370 . 13) (100 . "AcDbLine") (10 13625.4524886878
5531.6742081448 0.0) (11 13690.9389140272 5531.6742081448 0.0))
((0 . "LINE") (100 . "AcDbEntity") (8 . "ARCH") (62 . 7) (370 . 13) (100 . "AcDbLine") (10 13690.9389140272
5531.6742081448 0.0) (11 13707.8959276018 5531.6742081448 0.0))
((0 . "LINE") (100 . "AcDbEntity") (8 . "ARCH") (62 . 7) (370 . 13) (100 . "AcDbLine") (10 13707.8959276018
5531.6742081448 0.0) (11 13772.3755656109 5531.6742081448 0.0))
((0 . "LINE") (100 . "AcDbEntity") (8 . "ARCH") (62 . 7) (370 . 13) (100 . "AcDbLine") (10 13772.3755656109
5531.6742081448 0.0) (11 13823.5294117647 5531.6742081448 0.0))
((0 . "LINE") (100 . "AcDbEntity") (8 . "ARCH") (62 . 7) (370 . 13) (100 . "AcDbLine") (10 13823.5294117647
5531.6742081448 0.0) (11 15361.9909502262 5531.6742081448 0.0))
((0 . "LINE") (100 . "AcDbEntity") (8 . "ARCH") (62 . 7) (370 . 13) (100 . "AcDbLine") (10 15361.9909502262
5531.6742081448 0.0) (11 15421.685520362 5531.6742081448 0.0))
((0 . "LINE") (100 . "AcDbEntity") (8 . "ARCH") (62 . 7) (370 . 13) (100 . "AcDbLine") (10 15421.685520362
5531.6742081448 0.0) (11 15438.7104072398 5531.6742081448 0.0))
((0 . "LINE") (100 . "AcDbEntity") (8 . "ARCH") (62 . 7) (370 . 13) (100 . "AcDbLine") (10 15438.7104072398
5531.6742081448 0.0) (11 15498.5972850679 5531.6742081448 0.0))
((0 . "LINE") (100 . "AcDbEntity") (8 . "ARCH") (62 . 7) (370 . 13) (100 . "AcDbLine") (10 15498.5972850679
5531.6742081448 0.0) (11 15516.2895927602 5531.6742081448 0.0))
((0 . "LINE") (100 . "AcDbEntity") (8 . "ARCH") (62 . 7) (370 . 13) (100 . "AcDbLine") (10 15516.2895927602
5531.6742081448 0.0) (11 15568.1674208145 5531.6742081448 0.0))
((0 . "LINE") (100 . "AcDbEntity") (8 . "ARCH") (62 . 7) (370 . 13) (100 . "AcDbLine") (10 15568.1674208145
5531.6742081448 0.0) (11 15618.9479638009 5531.6742081448 0.0))
((0 . "LINE") (100 . "AcDbEntity") (8 . "ARCH") (62 . 7) (370 . 13) (100 . "AcDbLine") (10 15618.9479638009
5531.6742081448 0.0) (11 15681.3461538462 5531.6742081448 0.0))
((0 . "LINE") (100 . "AcDbEntity") (8 . "ARCH") (62 . 7) (370 . 13) (100 . "AcDbLine") (10 15681.3461538462
5531.6742081448 0.0) (11 15698.7330316742 5531.6742081448 0.0))
((0 . "LINE") (100 . "AcDbEntity") (8 . "ARCH") (62 . 7) (370 . 13) (100 . "AcDbLine") (10 15698.7330316742
5531.6742081448 0.0) (11 15748.834841629 5531.6742081448 0.0))
((0 . "LINE") (100 . "AcDbEntity") (8 . "ARCH") (62 . 7) (370 . 13) (100 . "AcDbLine") (10 15748.834841629
5531.6742081448 0.0) (11 15775.2941176471 5531.6742081448 0.0))
((0 . "LINE") (100 . "AcDbEntity") (8 . "ARCH") (62 . 7) (370 . 13) (100 . "AcDbLine") (10 15775.2941176471
5531.6742081448 0.0) (11 15825.7918552036 5531.6742081448 0.0))
((0 . "LINE") (100 . "AcDbEntity") (8 . "ARCH") (62 . 7) (370 . 13) (100 . "AcDbLine") (10 13314.4796380091
5588.2352941176 0.0) (11 15825.7918552036 5588.2352941176 0.0))
((0 . "LINE") (100 . "AcDbEntity") (8 . "ARCH") (62 . 7) (370 . 13) (100 . "AcDbLine") (10 15825.7918552036
5588.2352941176 0.0) (11 15837.1040723982 5588.2352941176 0.0))
((0 . "LINE") (100 . "AcDbEntity") (8 . "ARCH") (62 . 7) (370 . 13) (100 . "AcDbLine") (10 13190.0452488688
3778.2805429864 0.0) (11 15938.9140271493 3778.2805429864 0.0))
((0 . "LINE") (100 . "AcDbEntity") (8 . "ARCH") (62 . 7) (370 . 13) (100 . "AcDbLine") (10 15938.9140271493
3778.2805429864 0.0) (11 15938.9140271493 3721.7194570136 0.0))
((0 . "LINE") (100 . "AcDbEntity") (8 . "ARCH") (62 . 7) (370 . 13) (100 . "AcDbLine") (10 15938.9140271493
3721.7194570136 0.0) (11 15938.9140271493 3585.9728506787 0.0))
((0 . "LINE") (100 . "AcDbEntity") (8 . "ARCH") (62 . 7) (370 . 13) (100 . "AcDbLine") (10 15938.9140271493
3585.9728506787 0.0) (11 15938.9140271493 3235.2941176471 0.0))
((0 . "LINE") (100 . "AcDbEntity") (8 . "ARCH") (62 . 7) (370 . 13) (100 . "AcDbLine") (10 15938.9140271493
3235.2941176471 0.0) (11 15927.6018099548 3235.2941176471 0.0))
((0 . "LINE") (100 . "AcDbEntity") (8 . "ARCH") (62 . 7) (370 . 13) (100 . "AcDbLine") (10 15927.6018099548
3235.2941176471 0.0) (11 13201.3574660633 3235.2941176471 0.0))
((0 . "LINE") (100 . "AcDbEntity") (8 . "ARCH") (62 . 7) (370 . 13) (100 . "AcDbLine") (10 13201.3574660633
3235.2941176471 0.0) (11 13190.0452488688 3235.2941176471 0.0))
((0 . "LINE") (100 . "AcDbEntity") (8 . "ARCH") (62 . 7) (370 . 13) (100 . "AcDbLine") (10 13190.0452488688
3235.2941176471 0.0) (11 13190.0452488688 3585.9728506787 0.0))
((0 . "LINE") (100 . "AcDbEntity") (8 . "ARCH") (62 . 7) (370 . 13) (100 . "AcDbLine") (10 13190.0452488688
3585.9728506787 0.0) (11 13190.0452488688 3721.7194570136 0.0))
((0 . "LINE") (100 . "AcDbEntity") (8 . "ARCH") (62 . 7) (370 . 13) (100 . "AcDbLine") (10 13190.0452488688
3721.7194570136 0.0) (11 13190.0452488688 3778.2805429864 0.0))
((0 . "LINE") (100 . "AcDbEntity") (8 . "ARCH") (62 . 7) (370 . 13) (100 . "AcDbLine") (10 15927.6018099548
3235.2941176471 0.0) (11 15927.6018099548 2941.1764705882 0.0))
((0 . "LINE") (100 . "AcDbEntity") (8 . "ARCH") (62 . 7) (370 . 13) (100 . "AcDbLine") (10 15927.6018099548
2941.1764705882 0.0) (11 13201.3574660633 2941.1764705882 0.0))
((0 . "LINE") (100 . "AcDbEntity") (8 . "ARCH") (62 . 7) (370 . 13) (100 . "AcDbLine") (10 13201.3574660633
2941.1764705882 0.0) (11 13201.3574660633 3235.2941176471 0.0))
((0 . "LINE") (100 . "AcDbEntity") (8 . "ARCH") (62 . 7) (370 . 13) (100 . "AcDbLine") (10 13178.7330316742
2941.1764705882 0.0) (11 13201.3574660633 2941.1764705882 0.0))
((0 . "LINE") (100 . "AcDbEntity") (8 . "ARCH") (62 . 7) (370 . 13) (100 . "AcDbLine") (10 15927.6018099548
2941.1764705882 0.0) (11 15938.9140271493 2941.1764705882 0.0))
((0 . "LINE") (100 . "AcDbEntity") (8 . "ARCH") (62 . 7) (370 . 13) (100 . "AcDbLine") (10 15938.9140271493
2941.1764705882 0.0) (11 15938.9140271493 2861.9909502262 0.0))
((0 . "LINE") (100 . "AcDbEntity") (8 . "ARCH") (62 . 7) (370 . 13) (100 . "AcDbLine") (10 15938.9140271493
2861.9909502262 0.0) (11 15916.2895927602 2861.9909502262 0.0))
((0 . "LINE") (100 . "AcDbEntity") (8 . "ARCH") (62 . 7) (370 . 13) (100 . "AcDbLine") (10 15916.2895927602
2861.9909502262 0.0) (11 13201.3574660633 2861.9909502262 0.0))
((0 . "LINE") (100 . "AcDbEntity") (8 . "ARCH") (62 . 7) (370 . 13) (100 . "AcDbLine") (10 13201.3574660633
2861.9909502262 0.0) (11 13178.7330316742 2861.9909502262 0.0))
((0 . "LINE") (100 . "AcDbEntity") (8 . "ARCH") (62 . 7) (370 . 13) (100 . "AcDbLine") (10 13178.7330316742
2861.9909502262 0.0) (11 13178.7330316742 2941.1764705882 0.0))
((0 . "LINE") (100 . "AcDbEntity") (8 . "ARCH") (62 . 7) (370 . 13) (100 . "AcDbLine") (10 13201.3574660633
2861.9909502262 0.0) (11 13269.2307692308 2794.1176470588 0.0))
((0 . "LINE") (100 . "AcDbEntity") (8 . "ARCH") (62 . 7) (370 . 13) (100 . "AcDbLine") (10 13269.2307692308
2794.1176470588 0.0) (11 13280.5429864253 2748.8687782805 0.0))
((0 . "LINE") (100 . "AcDbEntity") (8 . "ARCH") (62 . 7) (370 . 13) (100 . "AcDbLine") (10 13280.5429864253
2748.8687782805 0.0) (11 13291.8552036199 2703.6199095023 0.0))
((0 . "LINE") (100 . "AcDbEntity") (8 . "ARCH") (62 . 7) (370 . 13) (100 . "AcDbLine") (10 13291.8552036199
2703.6199095023 0.0) (11 15837.1040723982 2703.6199095023 0.0))
((0 . "LINE") (100 . "AcDbEntity") (8 . "ARCH") (62 . 7) (370 . 13) (100 . "AcDbLine") (10 15837.1040723982
2703.6199095023 0.0) (11 15848.4162895928 2748.8687782805 0.0))
((0 . "LINE") (100 . "AcDbEntity") (8 . "ARCH") (62 . 7) (370 . 13) (100 . "AcDbLine") (10 15848.4162895928
2748.8687782805 0.0) (11 15859.7285067873 2794.1176470588 0.0))
((0 . "LINE") (100 . "AcDbEntity") (8 . "ARCH") (62 . 7) (370 . 13) (100 . "AcDbLine") (10 15859.7285067873
2794.1176470588 0.0) (11 15916.2895927602 2861.9909502262 0.0))
((0 . "LINE") (100 . "AcDbEntity") (8 . "ARCH") (62 . 7) (370 . 13) (100 . "AcDbLine") (10 13280.5429864253
2748.8687782805 0.0) (11 15848.4162895928 2748.8687782805 0.0))
((0 . "LINE") (100 . "AcDbEntity") (8 . "ARCH") (62 . 7) (370 . 13) (100 . "AcDbLine") (10 13291.8552036199
938.9140271493 0.0) (11 15871.0407239819 938.9140271493 0.0))
((0 . "LINE") (100 . "AcDbEntity") (8 . "ARCH") (62 . 7) (370 . 13) (100 . "AcDbLine") (10 15871.0407239819
938.9140271493 0.0) (11 15871.0407239819 859.7285067873 0.0))
((0 . "LINE") (100 . "AcDbEntity") (8 . "ARCH") (62 . 7) (370 . 13) (100 . "AcDbLine") (10 15871.0407239819
859.7285067873 0.0) (11 15803.1674208145 859.7285067873 0.0))
((0 . "LINE") (100 . "AcDbEntity") (8 . "ARCH") (62 . 7) (370 . 13) (100 . "AcDbLine") (10 15803.1674208145
859.7285067873 0.0) (11 13359.7285067873 859.7285067873 0.0))
((0 . "LINE") (100 . "AcDbEntity") (8 . "ARCH") (62 . 7) (370 . 13) (100 . "AcDbLine") (10 13359.7285067873
859.7285067873 0.0) (11 13291.8552036199 859.7285067873 0.0))
((0 . "LINE") (100 . "AcDbEntity") (8 . "ARCH") (62 . 7) (370 . 13) (100 . "AcDbLine") (10 13291.8552036199
859.7285067873 0.0) (11 13291.8552036199 938.9140271493 0.0))
((0 . "LINE") (100 . "AcDbEntity") (8 . "ARCH") (62 . 7) (370 . 13) (100 . "AcDbLine") (10 15803.1674208145
859.7285067873 0.0) (11 15803.1674208145 599.5475113122 0.0))
((0 . "LINE") (100 . "AcDbEntity") (8 . "ARCH") (62 . 7) (370 . 13) (100 . "AcDbLine") (10 15803.1674208145
599.5475113122 0.0) (11 13359.7285067873 599.5475113122 0.0))
((0 . "LINE") (100 . "AcDbEntity") (8 . "ARCH") (62 . 7) (370 . 13) (100 . "AcDbLine") (10 13359.7285067873
599.5475113122 0.0) (11 13359.7285067873 859.7285067873 0.0))
((0 . "LINE") (100 . "AcDbEntity") (8 . "ARCH") (62 . 7) (370 . 13) (100 . "AcDbLine") (10 13359.7285067873
576.9230769231 0.0) (11 15803.1674208145 576.9230769231 0.0))
((0 . "LINE") (100 . "AcDbEntity") (8 . "ARCH") (62 . 7) (370 . 13) (100 . "AcDbLine") (10 12601.8099547511
3382.3529411765 0.0) (11 12726.2443438914 3382.3529411765 0.0))
((0 . "LINE") (100 . "AcDbEntity") (8 . "ARCH") (62 . 7) (370 . 13) (100 . "AcDbLine") (10 12726.2443438914
3382.3529411765 0.0) (11 12726.2443438914 2533.9366515837 0.0))
((0 . "LINE") (100 . "AcDbEntity") (8 . "ARCH") (62 . 7) (370 . 13) (100 . "AcDbLine") (10 12726.2443438914
2533.9366515837 0.0) (11 12601.8099547511 2533.9366515837 0.0))
((0 . "LINE") (100 . "AcDbEntity") (8 . "ARCH") (62 . 7) (370 . 13) (100 . "AcDbLine") (10 12601.8099547511
2533.9366515837 0.0) (11 12601.8099547511 3382.3529411765 0.0))
((0 . "LINE") (100 . "AcDbEntity") (8 . "ARCH") (62 . 7) (370 . 13) (100 . "AcDbLine") (10 12635.7466063348
3337.1040723982 0.0) (11 12692.3076923077 3337.1040723982 0.0))
((0 . "LINE") (100 . "AcDbEntity") (8 . "ARCH") (62 . 7) (370 . 13) (100 . "AcDbLine") (10 12692.3076923077
3337.1040723982 0.0) (11 12692.3076923077 2590.4977375566 0.0))
((0 . "LINE") (100 . "AcDbEntity") (8 . "ARCH") (62 . 7) (370 . 13) (100 . "AcDbLine") (10 12692.3076923077
2590.4977375566 0.0) (11 12635.7466063348 2590.4977375566 0.0))
((0 . "LINE") (100 . "AcDbEntity") (8 . "ARCH") (62 . 7) (370 . 13) (100 . "AcDbLine") (10 12635.7466063348
2590.4977375566 0.0) (11 12635.7466063348 3337.1040723982 0.0))
((0 . "LINE") (100 . "AcDbEntity") (8 . "ARCH") (62 . 7) (370 . 13) (100 . "AcDbLine") (10 16481.9004524887
3382.3529411765 0.0) (11 16606.334841629 3382.3529411765 0.0))
((0 . "LINE") (100 . "AcDbEntity") (8 . "ARCH") (62 . 7) (370 . 13) (100 . "AcDbLine") (10 16606.334841629
3382.3529411765 0.0) (11 16606.334841629 2533.9366515837 0.0))
((0 . "LINE") (100 . "AcDbEntity") (8 . "ARCH") (62 . 7) (370 . 13) (100 . "AcDbLine") (10 16606.334841629
2533.9366515837 0.0) (11 16481.9004524887 2533.9366515837 0.0))
((0 . "LINE") (100 . "AcDbEntity") (8 . "ARCH") (62 . 7) (370 . 13) (100 . "AcDbLine") (10 16481.9004524887
2533.9366515837 0.0) (11 16481.9004524887 3382.3529411765 0.0))
((0 . "LINE") (100 . "AcDbEntity") (8 . "ARCH") (62 . 7) (370 . 13) (100 . "AcDbLine") (10 16515.8371040724
3337.1040723982 0.0) (11 16572.3981900452 3337.1040723982 0.0))
((0 . "LINE") (100 . "AcDbEntity") (8 . "ARCH") (62 . 7) (370 . 13) (100 . "AcDbLine") (10 16572.3981900452
3337.1040723982 0.0) (11 16572.3981900452 2590.4977375566 0.0))
((0 . "LINE") (100 . "AcDbEntity") (8 . "ARCH") (62 . 7) (370 . 13) (100 . "AcDbLine") (10 16572.3981900452
2590.4977375566 0.0) (11 16515.8371040724 2590.4977375566 0.0))
((0 . "LINE") (100 . "AcDbEntity") (8 . "ARCH") (62 . 7) (370 . 13) (100 . "AcDbLine") (10 16515.8371040724
2590.4977375566 0.0) (11 16515.8371040724 3337.1040723982 0.0))
((0 . "LINE") (100 . "AcDbEntity") (8 . "ARCH") (62 . 7) (370 . 13) (100 . "AcDbLine") (10 995.4751131222
3812.2171945701 0.0) (11 2398.1900452489 3812.2171945701 0.0))
((0 . "LINE") (100 . "AcDbEntity") (8 . "ARCH") (62 . 7) (370 . 13) (100 . "AcDbLine") (10 2398.1900452489
3812.2171945701 0.0) (11 2398.1900452489 3303.1674208145 0.0))
((0 . "LINE") (100 . "AcDbEntity") (8 . "ARCH") (62 . 7) (370 . 13) (100 . "AcDbLine") (10 2398.1900452489
3303.1674208145 0.0) (11 2398.1900452489 3280.5429864253 0.0))
((0 . "LINE") (100 . "AcDbEntity") (8 . "ARCH") (62 . 7) (370 . 13) (100 . "AcDbLine") (10 2398.1900452489
3280.5429864253 0.0) (11 995.4751131222 3280.5429864253 0.0))
((0 . "LINE") (100 . "AcDbEntity") (8 . "ARCH") (62 . 7) (370 . 13) (100 . "AcDbLine") (10 995.4751131222
3280.5429864253 0.0) (11 995.4751131222 3303.1674208145 0.0))
((0 . "LINE") (100 . "AcDbEntity") (8 . "ARCH") (62 . 7) (370 . 13) (100 . "AcDbLine") (10 995.4751131222
3303.1674208145 0.0) (11 995.4751131222 3812.2171945701 0.0))
((0 . "LINE") (100 . "AcDbEntity") (8 . "ARCH") (62 . 7) (370 . 13) (100 . "AcDbLine") (10 1040.7239819005
3766.9683257919 0.0) (11 1040.7239819005 3694.7171945701 0.0))
((0 . "LINE") (100 . "AcDbEntity") (8 . "ARCH") (62 . 7) (370 . 13) (100 . "AcDbLine") (10 1040.7239819005
3694.7171945701 0.0) (11 1040.7239819005 3654.5248868778 0.0))
((0 . "LINE") (100 . "AcDbEntity") (8 . "ARCH") (62 . 7) (370 . 13) (100 . "AcDbLine") (10 1040.7239819005
3654.5248868778 0.0) (11 1040.7239819005 3628.1108597285 0.0))
((0 . "LINE") (100 . "AcDbEntity") (8 . "ARCH") (62 . 7) (370 . 13) (100 . "AcDbLine") (10 1040.7239819005
3628.1108597285 0.0) (11 1040.7239819005 3590.8597285068 0.0))
((0 . "LINE") (100 . "AcDbEntity") (8 . "ARCH") (62 . 7) (370 . 13) (100 . "AcDbLine") (10 1040.7239819005
3590.8597285068 0.0) (11 1040.7239819005 3538.5180995475 0.0))
((0 . "LINE") (100 . "AcDbEntity") (8 . "ARCH") (62 . 7) (370 . 13) (100 . "AcDbLine") (10 1040.7239819005
3538.5180995475 0.0) (11 1040.7239819005 3476.8778280543 0.0))
((0 . "LINE") (100 . "AcDbEntity") (8 . "ARCH") (62 . 7) (370 . 13) (100 . "AcDbLine") (10 1040.7239819005
3476.8778280543 0.0) (11 1040.7239819005 3437.149321267 0.0))
((0 . "LINE") (100 . "AcDbEntity") (8 . "ARCH") (62 . 7) (370 . 13) (100 . "AcDbLine") (10 1040.7239819005
3437.149321267 0.0) (11 1040.7239819005 3405.6900452489 0.0))
((0 . "LINE") (100 . "AcDbEntity") (8 . "ARCH") (62 . 7) (370 . 13) (100 . "AcDbLine") (10 1040.7239819005
3405.6900452489 0.0) (11 1040.7239819005 3371.2669683258 0.0))
((0 . "LINE") (100 . "AcDbEntity") (8 . "ARCH") (62 . 7) (370 . 13) (100 . "AcDbLine") (10 1040.7239819005
3371.2669683258 0.0) (11 1040.7239819005 3325.7918552036 0.0))
((0 . "LINE") (100 . "AcDbEntity") (8 . "ARCH") (62 . 7) (370 . 13) (100 . "AcDbLine") (10 2352.9411764706
3766.9683257919 0.0) (11 2352.9411764706 3694.7171945701 0.0))
((0 . "LINE") (100 . "AcDbEntity") (8 . "ARCH") (62 . 7) (370 . 13) (100 . "AcDbLine") (10 2352.9411764706
3694.7171945701 0.0) (11 2352.9411764706 3654.5248868778 0.0))
((0 . "LINE") (100 . "AcDbEntity") (8 . "ARCH") (62 . 7) (370 . 13) (100 . "AcDbLine") (10 2352.9411764706
3654.5248868778 0.0) (11 2352.9411764706 3628.1108597285 0.0))
((0 . "LINE") (100 . "AcDbEntity") (8 . "ARCH") (62 . 7) (370 . 13) (100 . "AcDbLine") (10 2352.9411764706
3628.1108597285 0.0) (11 2352.9411764706 3590.8597285068 0.0))
((0 . "LINE") (100 . "AcDbEntity") (8 . "ARCH") (62 . 7) (370 . 13) (100 . "AcDbLine") (10 2352.9411764706
3590.8597285068 0.0) (11 2352.9411764706 3538.5180995475 0.0))
((0 . "LINE") (100 . "AcDbEntity") (8 . "ARCH") (62 . 7) (370 . 13) (100 . "AcDbLine") (10 2352.9411764706
3538.5180995475 0.0) (11 2352.9411764706 3476.8778280543 0.0))
((0 . "LINE") (100 . "AcDbEntity") (8 . "ARCH") (62 . 7) (370 . 13) (100 . "AcDbLine") (10 2352.9411764706
3476.8778280543 0.0) (11 2352.9411764706 3437.149321267 0.0))
((0 . "LINE") (100 . "AcDbEntity") (8 . "ARCH") (62 . 7) (370 . 13) (100 . "AcDbLine") (10 2352.9411764706
3437.149321267 0.0) (11 2352.9411764706 3405.6900452489 0.0))
((0 . "LINE") (100 . "AcDbEntity") (8 . "ARCH") (62 . 7) (370 . 13) (100 . "AcDbLine") (10 2352.9411764706
3405.6900452489 0.0) (11 2352.9411764706 3371.2669683258 0.0))
((0 . "LINE") (100 . "AcDbEntity") (8 . "ARCH") (62 . 7) (370 . 13) (100 . "AcDbLine") (10 2352.9411764706
3371.2669683258 0.0) (11 2352.9411764706 3303.1674208145 0.0))
((0 . "LINE") (100 . "AcDbEntity") (8 . "ARCH") (62 . 7) (370 . 13) (100 . "AcDbLine") (10 1040.7239819005
3694.7171945701 0.0) (11 2352.9411764706 3694.7171945701 0.0))
((0 . "LINE") (100 . "AcDbEntity") (8 . "ARCH") (62 . 7) (370 . 13) (100 . "AcDbLine") (10 1040.7239819005
3654.5248868778 0.0) (11 2352.9411764706 3654.5248868778 0.0))
((0 . "LINE") (100 . "AcDbEntity") (8 . "ARCH") (62 . 7) (370 . 13) (100 . "AcDbLine") (10 1040.7239819005
3628.1108597285 0.0) (11 2352.9411764706 3628.1108597285 0.0))
((0 . "LINE") (100 . "AcDbEntity") (8 . "ARCH") (62 . 7) (370 . 13) (100 . "AcDbLine") (10 1040.7239819005
3590.8597285068 0.0) (11 2352.9411764706 3590.8597285068 0.0))
((0 . "LINE") (100 . "AcDbEntity") (8 . "ARCH") (62 . 7) (370 . 13) (100 . "AcDbLine") (10 1040.7239819005
3538.5180995475 0.0) (11 2352.9411764706 3538.5180995475 0.0))
((0 . "LINE") (100 . "AcDbEntity") (8 . "ARCH") (62 . 7) (370 . 13) (100 . "AcDbLine") (10 1040.7239819005
3476.8778280543 0.0) (11 2352.9411764706 3476.8778280543 0.0))
((0 . "LINE") (100 . "AcDbEntity") (8 . "ARCH") (62 . 7) (370 . 13) (100 . "AcDbLine") (10 1040.7239819005
3437.149321267 0.0) (11 2352.9411764706 3437.149321267 0.0))
((0 . "LINE") (100 . "AcDbEntity") (8 . "ARCH") (62 . 7) (370 . 13) (100 . "AcDbLine") (10 1040.7239819005
3405.6900452489 0.0) (11 2352.9411764706 3405.6900452489 0.0))
((0 . "LINE") (100 . "AcDbEntity") (8 . "ARCH") (62 . 7) (370 . 13) (100 . "AcDbLine") (10 1040.7239819005
3371.2669683258 0.0) (11 2352.9411764706 3371.2669683258 0.0))
((0 . "LINE") (100 . "AcDbEntity") (8 . "ARCH") (62 . 7) (370 . 13) (100 . "AcDbLine") (10 972.850678733 3303.1674208145
0.0) (11 995.4751131222 3303.1674208145 0.0))
((0 . "LINE") (100 . "AcDbEntity") (8 . "ARCH") (62 . 7) (370 . 13) (100 . "AcDbLine") (10 995.4751131222
3303.1674208145 0.0) (11 2352.9411764706 3303.1674208145 0.0))
((0 . "LINE") (100 . "AcDbEntity") (8 . "ARCH") (62 . 7) (370 . 13) (100 . "AcDbLine") (10 2352.9411764706
3303.1674208145 0.0) (11 2398.1900452489 3303.1674208145 0.0))
((0 . "LINE") (100 . "AcDbEntity") (8 . "ARCH") (62 . 7) (370 . 13) (100 . "AcDbLine") (10 2398.1900452489
3303.1674208145 0.0) (11 2420.814479638 3303.1674208145 0.0))
((0 . "LINE") (100 . "AcDbEntity") (8 . "ARCH") (62 . 7) (370 . 13) (100 . "AcDbLine") (10 1006.7873303167
1018.0995475113 0.0) (11 2533.9366515837 1018.0995475113 0.0))
((0 . "LINE") (100 . "AcDbEntity") (8 . "ARCH") (62 . 7) (370 . 13) (100 . "AcDbLine") (10 2533.9366515837
1018.0995475113 0.0) (11 2533.9366515837 520.3619909502 0.0))
((0 . "LINE") (100 . "AcDbEntity") (8 . "ARCH") (62 . 7) (370 . 13) (100 . "AcDbLine") (10 2533.9366515837
520.3619909502 0.0) (11 2533.9366515837 497.7375565611 0.0))
((0 . "LINE") (100 . "AcDbEntity") (8 . "ARCH") (62 . 7) (370 . 13) (100 . "AcDbLine") (10 2533.9366515837
497.7375565611 0.0) (11 1006.7873303167 497.7375565611 0.0))
((0 . "LINE") (100 . "AcDbEntity") (8 . "ARCH") (62 . 7) (370 . 13) (100 . "AcDbLine") (10 1006.7873303167
497.7375565611 0.0) (11 1006.7873303167 520.3619909502 0.0))
((0 . "LINE") (100 . "AcDbEntity") (8 . "ARCH") (62 . 7) (370 . 13) (100 . "AcDbLine") (10 1006.7873303167
520.3619909502 0.0) (11 1006.7873303167 1018.0995475113 0.0))
((0 . "LINE") (100 . "AcDbEntity") (8 . "ARCH") (62 . 7) (370 . 13) (100 . "AcDbLine") (10 1052.036199095 972.850678733
0.0) (11 1052.036199095 938.3371040724 0.0))
((0 . "LINE") (100 . "AcDbEntity") (8 . "ARCH") (62 . 7) (370 . 13) (100 . "AcDbLine") (10 1052.036199095 938.3371040724
0.0) (11 1052.036199095 890.7126696833 0.0))
((0 . "LINE") (100 . "AcDbEntity") (8 . "ARCH") (62 . 7) (370 . 13) (100 . "AcDbLine") (10 1052.036199095 890.7126696833
0.0) (11 1052.036199095 856.7986425339 0.0))
((0 . "LINE") (100 . "AcDbEntity") (8 . "ARCH") (62 . 7) (370 . 13) (100 . "AcDbLine") (10 1052.036199095 856.7986425339
0.0) (11 1052.036199095 820.7013574661 0.0))
((0 . "LINE") (100 . "AcDbEntity") (8 . "ARCH") (62 . 7) (370 . 13) (100 . "AcDbLine") (10 1052.036199095 820.7013574661
0.0) (11 1052.036199095 756.3235294118 0.0))
((0 . "LINE") (100 . "AcDbEntity") (8 . "ARCH") (62 . 7) (370 . 13) (100 . "AcDbLine") (10 1052.036199095 756.3235294118
0.0) (11 1052.036199095 692.7375565611 0.0))
((0 . "LINE") (100 . "AcDbEntity") (8 . "ARCH") (62 . 7) (370 . 13) (100 . "AcDbLine") (10 1052.036199095 692.7375565611
0.0) (11 1052.036199095 634.3665158371 0.0))
((0 . "LINE") (100 . "AcDbEntity") (8 . "ARCH") (62 . 7) (370 . 13) (100 . "AcDbLine") (10 1052.036199095 634.3665158371
0.0) (11 1052.036199095 597.0022624434 0.0))
((0 . "LINE") (100 . "AcDbEntity") (8 . "ARCH") (62 . 7) (370 . 13) (100 . "AcDbLine") (10 1052.036199095 597.0022624434
0.0) (11 1052.036199095 575.3393665158 0.0))
((0 . "LINE") (100 . "AcDbEntity") (8 . "ARCH") (62 . 7) (370 . 13) (100 . "AcDbLine") (10 1052.036199095 575.3393665158
0.0) (11 1052.036199095 542.9864253394 0.0))
((0 . "LINE") (100 . "AcDbEntity") (8 . "ARCH") (62 . 7) (370 . 13) (100 . "AcDbLine") (10 2488.6877828054 972.850678733
0.0) (11 2488.6877828054 938.3371040724 0.0))
((0 . "LINE") (100 . "AcDbEntity") (8 . "ARCH") (62 . 7) (370 . 13) (100 . "AcDbLine") (10 2488.6877828054
938.3371040724 0.0) (11 2488.6877828054 890.7126696833 0.0))
((0 . "LINE") (100 . "AcDbEntity") (8 . "ARCH") (62 . 7) (370 . 13) (100 . "AcDbLine") (10 2488.6877828054
890.7126696833 0.0) (11 2488.6877828054 856.7986425339 0.0))
((0 . "LINE") (100 . "AcDbEntity") (8 . "ARCH") (62 . 7) (370 . 13) (100 . "AcDbLine") (10 2488.6877828054
856.7986425339 0.0) (11 2488.6877828054 820.7013574661 0.0))
((0 . "LINE") (100 . "AcDbEntity") (8 . "ARCH") (62 . 7) (370 . 13) (100 . "AcDbLine") (10 2488.6877828054
820.7013574661 0.0) (11 2488.6877828054 756.3235294118 0.0))
((0 . "LINE") (100 . "AcDbEntity") (8 . "ARCH") (62 . 7) (370 . 13) (100 . "AcDbLine") (10 2488.6877828054
756.3235294118 0.0) (11 2488.6877828054 692.7375565611 0.0))
((0 . "LINE") (100 . "AcDbEntity") (8 . "ARCH") (62 . 7) (370 . 13) (100 . "AcDbLine") (10 2488.6877828054
692.7375565611 0.0) (11 2488.6877828054 634.3665158371 0.0))
((0 . "LINE") (100 . "AcDbEntity") (8 . "ARCH") (62 . 7) (370 . 13) (100 . "AcDbLine") (10 2488.6877828054
634.3665158371 0.0) (11 2488.6877828054 597.0022624434 0.0))
((0 . "LINE") (100 . "AcDbEntity") (8 . "ARCH") (62 . 7) (370 . 13) (100 . "AcDbLine") (10 2488.6877828054
597.0022624434 0.0) (11 2488.6877828054 575.3393665158 0.0))
((0 . "LINE") (100 . "AcDbEntity") (8 . "ARCH") (62 . 7) (370 . 13) (100 . "AcDbLine") (10 2488.6877828054
575.3393665158 0.0) (11 2488.6877828054 520.3619909502 0.0))
((0 . "LINE") (100 . "AcDbEntity") (8 . "ARCH") (62 . 7) (370 . 13) (100 . "AcDbLine") (10 1052.036199095 938.3371040724
0.0) (11 2488.6877828054 938.3371040724 0.0))
((0 . "LINE") (100 . "AcDbEntity") (8 . "ARCH") (62 . 7) (370 . 13) (100 . "AcDbLine") (10 1052.036199095 890.7126696833
0.0) (11 2488.6877828054 890.7126696833 0.0))
((0 . "LINE") (100 . "AcDbEntity") (8 . "ARCH") (62 . 7) (370 . 13) (100 . "AcDbLine") (10 1052.036199095 856.7986425339
0.0) (11 2488.6877828054 856.7986425339 0.0))
((0 . "LINE") (100 . "AcDbEntity") (8 . "ARCH") (62 . 7) (370 . 13) (100 . "AcDbLine") (10 1052.036199095 820.7013574661
0.0) (11 2488.6877828054 820.7013574661 0.0))
((0 . "LINE") (100 . "AcDbEntity") (8 . "ARCH") (62 . 7) (370 . 13) (100 . "AcDbLine") (10 1052.036199095 756.3235294118
0.0) (11 2488.6877828054 756.3235294118 0.0))
((0 . "LINE") (100 . "AcDbEntity") (8 . "ARCH") (62 . 7) (370 . 13) (100 . "AcDbLine") (10 1052.036199095 692.7375565611
0.0) (11 2488.6877828054 692.7375565611 0.0))
((0 . "LINE") (100 . "AcDbEntity") (8 . "ARCH") (62 . 7) (370 . 13) (100 . "AcDbLine") (10 1052.036199095 634.3665158371
0.0) (11 2488.6877828054 634.3665158371 0.0))
((0 . "LINE") (100 . "AcDbEntity") (8 . "ARCH") (62 . 7) (370 . 13) (100 . "AcDbLine") (10 1052.036199095 597.0022624434
0.0) (11 2488.6877828054 597.0022624434 0.0))
((0 . "LINE") (100 . "AcDbEntity") (8 . "ARCH") (62 . 7) (370 . 13) (100 . "AcDbLine") (10 1052.036199095 575.3393665158
0.0) (11 2488.6877828054 575.3393665158 0.0))
((0 . "LINE") (100 . "AcDbEntity") (8 . "ARCH") (62 . 7) (370 . 13) (100 . "AcDbLine") (10 984.1628959276 520.3619909502
0.0) (11 1006.7873303167 520.3619909502 0.0))
((0 . "LINE") (100 . "AcDbEntity") (8 . "ARCH") (62 . 7) (370 . 13) (100 . "AcDbLine") (10 1006.7873303167
520.3619909502 0.0) (11 2488.6877828054 520.3619909502 0.0))
((0 . "LINE") (100 . "AcDbEntity") (8 . "ARCH") (62 . 7) (370 . 13) (100 . "AcDbLine") (10 2488.6877828054
520.3619909502 0.0) (11 2533.9366515837 520.3619909502 0.0))
((0 . "LINE") (100 . "AcDbEntity") (8 . "ARCH") (62 . 7) (370 . 13) (100 . "AcDbLine") (10 2533.9366515837
520.3619909502 0.0) (11 2556.5610859729 520.3619909502 0.0))
((0 . "LINE") (100 . "AcDbEntity") (8 . "ARCH") (62 . 7) (370 . 13) (100 . "AcDbLine") (10 17624.4343891403
3812.2171945701 0.0) (11 19049.7737556561 3812.2171945701 0.0))
((0 . "LINE") (100 . "AcDbEntity") (8 . "ARCH") (62 . 7) (370 . 13) (100 . "AcDbLine") (10 19049.7737556561
3812.2171945701 0.0) (11 19049.7737556561 3303.1674208145 0.0))
((0 . "LINE") (100 . "AcDbEntity") (8 . "ARCH") (62 . 7) (370 . 13) (100 . "AcDbLine") (10 19049.7737556561
3303.1674208145 0.0) (11 19049.7737556561 3280.5429864253 0.0))
((0 . "LINE") (100 . "AcDbEntity") (8 . "ARCH") (62 . 7) (370 . 13) (100 . "AcDbLine") (10 19049.7737556561
3280.5429864253 0.0) (11 17624.4343891403 3280.5429864253 0.0))
((0 . "LINE") (100 . "AcDbEntity") (8 . "ARCH") (62 . 7) (370 . 13) (100 . "AcDbLine") (10 17624.4343891403
3280.5429864253 0.0) (11 17624.4343891403 3303.1674208145 0.0))
((0 . "LINE") (100 . "AcDbEntity") (8 . "ARCH") (62 . 7) (370 . 13) (100 . "AcDbLine") (10 17624.4343891403
3303.1674208145 0.0) (11 17624.4343891403 3812.2171945701 0.0))
((0 . "LINE") (100 . "AcDbEntity") (8 . "ARCH") (62 . 7) (370 . 13) (100 . "AcDbLine") (10 17669.6832579186
3766.9683257919 0.0) (11 17669.6832579186 3696.0746606335 0.0))
((0 . "LINE") (100 . "AcDbEntity") (8 . "ARCH") (62 . 7) (370 . 13) (100 . "AcDbLine") (10 17669.6832579186
3696.0746606335 0.0) (11 17669.6832579186 3654.5588235294 0.0))
((0 . "LINE") (100 . "AcDbEntity") (8 . "ARCH") (62 . 7) (370 . 13) (100 . "AcDbLine") (10 17669.6832579186
3654.5588235294 0.0) (11 17669.6832579186 3624.1176470588 0.0))
((0 . "LINE") (100 . "AcDbEntity") (8 . "ARCH") (62 . 7) (370 . 13) (100 . "AcDbLine") (10 17669.6832579186
3624.1176470588 0.0) (11 17669.6832579186 3586.8212669683 0.0))
((0 . "LINE") (100 . "AcDbEntity") (8 . "ARCH") (62 . 7) (370 . 13) (100 . "AcDbLine") (10 17669.6832579186
3586.8212669683 0.0) (11 17669.6832579186 3536.9343891403 0.0))
((0 . "LINE") (100 . "AcDbEntity") (8 . "ARCH") (62 . 7) (370 . 13) (100 . "AcDbLine") (10 17669.6832579186
3536.9343891403 0.0) (11 17669.6832579186 3476.5610859729 0.0))
((0 . "LINE") (100 . "AcDbEntity") (8 . "ARCH") (62 . 7) (370 . 13) (100 . "AcDbLine") (10 17669.6832579186
3476.5610859729 0.0) (11 17669.6832579186 3438.5067873303 0.0))
((0 . "LINE") (100 . "AcDbEntity") (8 . "ARCH") (62 . 7) (370 . 13) (100 . "AcDbLine") (10 17669.6832579186
3438.5067873303 0.0) (11 17669.6832579186 3404.4117647059 0.0))
((0 . "LINE") (100 . "AcDbEntity") (8 . "ARCH") (62 . 7) (370 . 13) (100 . "AcDbLine") (10 17669.6832579186
3404.4117647059 0.0) (11 17669.6832579186 3371.3574660633 0.0))
((0 . "LINE") (100 . "AcDbEntity") (8 . "ARCH") (62 . 7) (370 . 13) (100 . "AcDbLine") (10 17669.6832579186
3371.3574660633 0.0) (11 17669.6832579186 3325.7918552036 0.0))
((0 . "LINE") (100 . "AcDbEntity") (8 . "ARCH") (62 . 7) (370 . 13) (100 . "AcDbLine") (10 19004.5248868778
3766.9683257919 0.0) (11 19004.5248868778 3696.0746606335 0.0))
((0 . "LINE") (100 . "AcDbEntity") (8 . "ARCH") (62 . 7) (370 . 13) (100 . "AcDbLine") (10 19004.5248868778
3696.0746606335 0.0) (11 19004.5248868778 3654.5588235294 0.0))
((0 . "LINE") (100 . "AcDbEntity") (8 . "ARCH") (62 . 7) (370 . 13) (100 . "AcDbLine") (10 19004.5248868778
3654.5588235294 0.0) (11 19004.5248868778 3624.1176470588 0.0))
((0 . "LINE") (100 . "AcDbEntity") (8 . "ARCH") (62 . 7) (370 . 13) (100 . "AcDbLine") (10 19004.5248868778
3624.1176470588 0.0) (11 19004.5248868778 3586.8212669683 0.0))
((0 . "LINE") (100 . "AcDbEntity") (8 . "ARCH") (62 . 7) (370 . 13) (100 . "AcDbLine") (10 19004.5248868778
3586.8212669683 0.0) (11 19004.5248868778 3536.9343891403 0.0))
((0 . "LINE") (100 . "AcDbEntity") (8 . "ARCH") (62 . 7) (370 . 13) (100 . "AcDbLine") (10 19004.5248868778
3536.9343891403 0.0) (11 19004.5248868778 3476.5610859729 0.0))
((0 . "LINE") (100 . "AcDbEntity") (8 . "ARCH") (62 . 7) (370 . 13) (100 . "AcDbLine") (10 19004.5248868778
3476.5610859729 0.0) (11 19004.5248868778 3438.5067873303 0.0))
((0 . "LINE") (100 . "AcDbEntity") (8 . "ARCH") (62 . 7) (370 . 13) (100 . "AcDbLine") (10 19004.5248868778
3438.5067873303 0.0) (11 19004.5248868778 3404.4117647059 0.0))
((0 . "LINE") (100 . "AcDbEntity") (8 . "ARCH") (62 . 7) (370 . 13) (100 . "AcDbLine") (10 19004.5248868778
3404.4117647059 0.0) (11 19004.5248868778 3371.3574660633 0.0))
((0 . "LINE") (100 . "AcDbEntity") (8 . "ARCH") (62 . 7) (370 . 13) (100 . "AcDbLine") (10 19004.5248868778
3371.3574660633 0.0) (11 19004.5248868778 3325.7918552036 0.0))
((0 . "LINE") (100 . "AcDbEntity") (8 . "ARCH") (62 . 7) (370 . 13) (100 . "AcDbLine") (10 17669.6832579186
3696.0746606335 0.0) (11 19004.5248868778 3696.0746606335 0.0))
((0 . "LINE") (100 . "AcDbEntity") (8 . "ARCH") (62 . 7) (370 . 13) (100 . "AcDbLine") (10 17669.6832579186
3654.5588235294 0.0) (11 19004.5248868778 3654.5588235294 0.0))
((0 . "LINE") (100 . "AcDbEntity") (8 . "ARCH") (62 . 7) (370 . 13) (100 . "AcDbLine") (10 17669.6832579186
3624.1176470588 0.0) (11 19004.5248868778 3624.1176470588 0.0))
((0 . "LINE") (100 . "AcDbEntity") (8 . "ARCH") (62 . 7) (370 . 13) (100 . "AcDbLine") (10 17669.6832579186
3586.8212669683 0.0) (11 19004.5248868778 3586.8212669683 0.0))
((0 . "LINE") (100 . "AcDbEntity") (8 . "ARCH") (62 . 7) (370 . 13) (100 . "AcDbLine") (10 17669.6832579186
3536.9343891403 0.0) (11 19004.5248868778 3536.9343891403 0.0))
((0 . "LINE") (100 . "AcDbEntity") (8 . "ARCH") (62 . 7) (370 . 13) (100 . "AcDbLine") (10 17669.6832579186
3476.5610859729 0.0) (11 19004.5248868778 3476.5610859729 0.0))
((0 . "LINE") (100 . "AcDbEntity") (8 . "ARCH") (62 . 7) (370 . 13) (100 . "AcDbLine") (10 17669.6832579186
3438.5067873303 0.0) (11 19004.5248868778 3438.5067873303 0.0))
((0 . "LINE") (100 . "AcDbEntity") (8 . "ARCH") (62 . 7) (370 . 13) (100 . "AcDbLine") (10 17669.6832579186
3404.4117647059 0.0) (11 19004.5248868778 3404.4117647059 0.0))
((0 . "LINE") (100 . "AcDbEntity") (8 . "ARCH") (62 . 7) (370 . 13) (100 . "AcDbLine") (10 17669.6832579186
3371.3574660633 0.0) (11 19004.5248868778 3371.3574660633 0.0))
((0 . "LINE") (100 . "AcDbEntity") (8 . "ARCH") (62 . 7) (370 . 13) (100 . "AcDbLine") (10 17601.8099547511
3303.1674208145 0.0) (11 17624.4343891403 3303.1674208145 0.0))
((0 . "LINE") (100 . "AcDbEntity") (8 . "ARCH") (62 . 7) (370 . 13) (100 . "AcDbLine") (10 17624.4343891403
3303.1674208145 0.0) (11 19049.7737556561 3303.1674208145 0.0))
((0 . "LINE") (100 . "AcDbEntity") (8 . "ARCH") (62 . 7) (370 . 13) (100 . "AcDbLine") (10 19049.7737556561
3303.1674208145 0.0) (11 19072.3981900452 3303.1674208145 0.0))
((0 . "LINE") (100 . "AcDbEntity") (8 . "ARCH") (62 . 7) (370 . 13) (100 . "AcDbLine") (10 17477.3755656109
1018.0995475113 0.0) (11 19038.4615384615 1018.0995475113 0.0))
((0 . "LINE") (100 . "AcDbEntity") (8 . "ARCH") (62 . 7) (370 . 13) (100 . "AcDbLine") (10 19038.4615384615
1018.0995475113 0.0) (11 19038.4615384615 520.3619909502 0.0))
((0 . "LINE") (100 . "AcDbEntity") (8 . "ARCH") (62 . 7) (370 . 13) (100 . "AcDbLine") (10 19038.4615384615
520.3619909502 0.0) (11 19038.4615384615 497.7375565611 0.0))
((0 . "LINE") (100 . "AcDbEntity") (8 . "ARCH") (62 . 7) (370 . 13) (100 . "AcDbLine") (10 19038.4615384615
497.7375565611 0.0) (11 17477.3755656109 497.7375565611 0.0))
((0 . "LINE") (100 . "AcDbEntity") (8 . "ARCH") (62 . 7) (370 . 13) (100 . "AcDbLine") (10 17477.3755656109
497.7375565611 0.0) (11 17477.3755656109 520.3619909502 0.0))
((0 . "LINE") (100 . "AcDbEntity") (8 . "ARCH") (62 . 7) (370 . 13) (100 . "AcDbLine") (10 17477.3755656109
520.3619909502 0.0) (11 17477.3755656109 1018.0995475113 0.0))
((0 . "LINE") (100 . "AcDbEntity") (8 . "ARCH") (62 . 7) (370 . 13) (100 . "AcDbLine") (10 17522.6244343891
972.850678733 0.0) (11 17522.6244343891 938.721719457 0.0))
((0 . "LINE") (100 . "AcDbEntity") (8 . "ARCH") (62 . 7) (370 . 13) (100 . "AcDbLine") (10 17522.6244343891
938.721719457 0.0) (11 17522.6244343891 890.3280542986 0.0))
((0 . "LINE") (100 . "AcDbEntity") (8 . "ARCH") (62 . 7) (370 . 13) (100 . "AcDbLine") (10 17522.6244343891
890.3280542986 0.0) (11 17522.6244343891 851.628959276 0.0))
((0 . "LINE") (100 . "AcDbEntity") (8 . "ARCH") (62 . 7) (370 . 13) (100 . "AcDbLine") (10 17522.6244343891
851.628959276 0.0) (11 17522.6244343891 812.036199095 0.0))
((0 . "LINE") (100 . "AcDbEntity") (8 . "ARCH") (62 . 7) (370 . 13) (100 . "AcDbLine") (10 17522.6244343891
812.036199095 0.0) (11 17522.6244343891 756.3914027149 0.0))
((0 . "LINE") (100 . "AcDbEntity") (8 . "ARCH") (62 . 7) (370 . 13) (100 . "AcDbLine") (10 17522.6244343891
756.3914027149 0.0) (11 17522.6244343891 691.8438914027 0.0))
((0 . "LINE") (100 . "AcDbEntity") (8 . "ARCH") (62 . 7) (370 . 13) (100 . "AcDbLine") (10 17522.6244343891
691.8438914027 0.0) (11 17522.6244343891 634.3325791855 0.0))
((0 . "LINE") (100 . "AcDbEntity") (8 . "ARCH") (62 . 7) (370 . 13) (100 . "AcDbLine") (10 17522.6244343891
634.3325791855 0.0) (11 17522.6244343891 571.1312217195 0.0))
((0 . "LINE") (100 . "AcDbEntity") (8 . "ARCH") (62 . 7) (370 . 13) (100 . "AcDbLine") (10 17522.6244343891
571.1312217195 0.0) (11 17522.6244343891 542.9864253394 0.0))
((0 . "LINE") (100 . "AcDbEntity") (8 . "ARCH") (62 . 7) (370 . 13) (100 . "AcDbLine") (10 18993.2126696833
972.850678733 0.0) (11 18993.2126696833 938.721719457 0.0))
((0 . "LINE") (100 . "AcDbEntity") (8 . "ARCH") (62 . 7) (370 . 13) (100 . "AcDbLine") (10 18993.2126696833
938.721719457 0.0) (11 18993.2126696833 890.3280542986 0.0))
((0 . "LINE") (100 . "AcDbEntity") (8 . "ARCH") (62 . 7) (370 . 13) (100 . "AcDbLine") (10 18993.2126696833
890.3280542986 0.0) (11 18993.2126696833 851.628959276 0.0))
((0 . "LINE") (100 . "AcDbEntity") (8 . "ARCH") (62 . 7) (370 . 13) (100 . "AcDbLine") (10 18993.2126696833
851.628959276 0.0) (11 18993.2126696833 812.036199095 0.0))
((0 . "LINE") (100 . "AcDbEntity") (8 . "ARCH") (62 . 7) (370 . 13) (100 . "AcDbLine") (10 18993.2126696833
812.036199095 0.0) (11 18993.2126696833 756.3914027149 0.0))
((0 . "LINE") (100 . "AcDbEntity") (8 . "ARCH") (62 . 7) (370 . 13) (100 . "AcDbLine") (10 18993.2126696833
756.3914027149 0.0) (11 18993.2126696833 691.8438914027 0.0))
((0 . "LINE") (100 . "AcDbEntity") (8 . "ARCH") (62 . 7) (370 . 13) (100 . "AcDbLine") (10 18993.2126696833
691.8438914027 0.0) (11 18993.2126696833 634.3325791855 0.0))
((0 . "LINE") (100 . "AcDbEntity") (8 . "ARCH") (62 . 7) (370 . 13) (100 . "AcDbLine") (10 18993.2126696833
634.3325791855 0.0) (11 18993.2126696833 571.1312217195 0.0))
((0 . "LINE") (100 . "AcDbEntity") (8 . "ARCH") (62 . 7) (370 . 13) (100 . "AcDbLine") (10 18993.2126696833
571.1312217195 0.0) (11 18993.2126696833 520.3619909502 0.0))
((0 . "LINE") (100 . "AcDbEntity") (8 . "ARCH") (62 . 7) (370 . 13) (100 . "AcDbLine") (10 17522.6244343891
938.721719457 0.0) (11 18993.2126696833 938.721719457 0.0))
((0 . "LINE") (100 . "AcDbEntity") (8 . "ARCH") (62 . 7) (370 . 13) (100 . "AcDbLine") (10 17522.6244343891
890.3280542986 0.0) (11 18993.2126696833 890.3280542986 0.0))
((0 . "LINE") (100 . "AcDbEntity") (8 . "ARCH") (62 . 7) (370 . 13) (100 . "AcDbLine") (10 17522.6244343891
851.628959276 0.0) (11 18993.2126696833 851.628959276 0.0))
((0 . "LINE") (100 . "AcDbEntity") (8 . "ARCH") (62 . 7) (370 . 13) (100 . "AcDbLine") (10 17522.6244343891
812.036199095 0.0) (11 18993.2126696833 812.036199095 0.0))
((0 . "LINE") (100 . "AcDbEntity") (8 . "ARCH") (62 . 7) (370 . 13) (100 . "AcDbLine") (10 17522.6244343891
756.3914027149 0.0) (11 18993.2126696833 756.3914027149 0.0))
((0 . "LINE") (100 . "AcDbEntity") (8 . "ARCH") (62 . 7) (370 . 13) (100 . "AcDbLine") (10 17522.6244343891
691.8438914027 0.0) (11 18993.2126696833 691.8438914027 0.0))
((0 . "LINE") (100 . "AcDbEntity") (8 . "ARCH") (62 . 7) (370 . 13) (100 . "AcDbLine") (10 17522.6244343891
634.3325791855 0.0) (11 18993.2126696833 634.3325791855 0.0))
((0 . "LINE") (100 . "AcDbEntity") (8 . "ARCH") (62 . 7) (370 . 13) (100 . "AcDbLine") (10 17522.6244343891
571.1312217195 0.0) (11 18993.2126696833 571.1312217195 0.0))
((0 . "LINE") (100 . "AcDbEntity") (8 . "ARCH") (62 . 7) (370 . 13) (100 . "AcDbLine") (10 17454.7511312217
520.3619909502 0.0) (11 17477.3755656109 520.3619909502 0.0))
((0 . "LINE") (100 . "AcDbEntity") (8 . "ARCH") (62 . 7) (370 . 13) (100 . "AcDbLine") (10 17477.3755656109
520.3619909502 0.0) (11 18993.2126696833 520.3619909502 0.0))
((0 . "LINE") (100 . "AcDbEntity") (8 . "ARCH") (62 . 7) (370 . 13) (100 . "AcDbLine") (10 18993.2126696833
520.3619909502 0.0) (11 19038.4615384615 520.3619909502 0.0))
((0 . "LINE") (100 . "AcDbEntity") (8 . "ARCH") (62 . 7) (370 . 13) (100 . "AcDbLine") (10 19038.4615384615
520.3619909502 0.0) (11 19061.0859728507 520.3619909502 0.0))
((0 . "LINE") (100 . "AcDbEntity") (8 . "ARCH") (62 . 7) (370 . 13) (100 . "AcDbLine") (10 8201.3574660633
3269.2307692308 0.0) (11 9309.9547511312 3269.2307692308 0.0))
((0 . "LINE") (100 . "AcDbEntity") (8 . "ARCH") (62 . 7) (370 . 13) (100 . "AcDbLine") (10 9309.9547511312
3269.2307692308 0.0) (11 9309.9547511312 3190.0452488688 0.0))
((0 . "LINE") (100 . "AcDbEntity") (8 . "ARCH") (62 . 7) (370 . 13) (100 . "AcDbLine") (10 9309.9547511312
3190.0452488688 0.0) (11 9287.3303167421 3190.0452488688 0.0))
((0 . "LINE") (100 . "AcDbEntity") (8 . "ARCH") (62 . 7) (370 . 13) (100 . "AcDbLine") (10 9287.3303167421
3190.0452488688 0.0) (11 8223.9819004525 3190.0452488688 0.0))
((0 . "LINE") (100 . "AcDbEntity") (8 . "ARCH") (62 . 7) (370 . 13) (100 . "AcDbLine") (10 8223.9819004525
3190.0452488688 0.0) (11 8201.3574660633 3190.0452488688 0.0))
((0 . "LINE") (100 . "AcDbEntity") (8 . "ARCH") (62 . 7) (370 . 13) (100 . "AcDbLine") (10 8201.3574660633
3190.0452488688 0.0) (11 8201.3574660633 3269.2307692308 0.0))
((0 . "LINE") (100 . "AcDbEntity") (8 . "ARCH") (62 . 7) (370 . 13) (100 . "AcDbLine") (10 8223.9819004525
3190.0452488688 0.0) (11 8291.8552036199 3122.1719457014 0.0))
((0 . "LINE") (100 . "AcDbEntity") (8 . "ARCH") (62 . 7) (370 . 13) (100 . "AcDbLine") (10 8291.8552036199
3122.1719457014 0.0) (11 8303.1674208145 3110.8597285068 0.0))
((0 . "LINE") (100 . "AcDbEntity") (8 . "ARCH") (62 . 7) (370 . 13) (100 . "AcDbLine") (10 8303.1674208145
3110.8597285068 0.0) (11 8314.4796380091 3076.9230769231 0.0))
((0 . "LINE") (100 . "AcDbEntity") (8 . "ARCH") (62 . 7) (370 . 13) (100 . "AcDbLine") (10 8314.4796380091
3076.9230769231 0.0) (11 9208.1447963801 3076.9230769231 0.0))
((0 . "LINE") (100 . "AcDbEntity") (8 . "ARCH") (62 . 7) (370 . 13) (100 . "AcDbLine") (10 9208.1447963801
3076.9230769231 0.0) (11 9219.4570135747 3110.8597285068 0.0))
((0 . "LINE") (100 . "AcDbEntity") (8 . "ARCH") (62 . 7) (370 . 13) (100 . "AcDbLine") (10 9219.4570135747
3110.8597285068 0.0) (11 9229.1532013575 3122.1719457014 0.0))
((0 . "LINE") (100 . "AcDbEntity") (8 . "ARCH") (62 . 7) (370 . 13) (100 . "AcDbLine") (10 9229.1532013575
3122.1719457014 0.0) (11 9287.3303167421 3190.0452488688 0.0))
((0 . "LINE") (100 . "AcDbEntity") (8 . "ARCH") (62 . 7) (370 . 13) (100 . "AcDbLine") (10 8291.8552036199
3122.1719457014 0.0) (11 9229.1532013575 3122.1719457014 0.0))
((0 . "LINE") (100 . "AcDbEntity") (8 . "ARCH") (62 . 7) (370 . 13) (100 . "AcDbLine") (10 9229.1532013575
3122.1719457014 0.0) (11 9230.7692307692 3122.1719457014 0.0))
((0 . "LINE") (100 . "AcDbEntity") (8 . "ARCH") (62 . 7) (370 . 13) (100 . "AcDbLine") (10 7929.8642533937 158.371040724
0.0) (11 9547.5113122172 158.371040724 0.0))
((0 . "LINE") (100 . "AcDbEntity") (8 . "ARCH") (62 . 7) (370 . 13) (100 . "AcDbLine") (10 7929.8642533937
101.8099547511 0.0) (11 9547.5113122172 101.8099547511 0.0))
((0 . "LINE") (100 . "AcDbEntity") (8 . "ARCH") (62 . 7) (370 . 13) (100 . "AcDbLine") (10 7929.8642533937 45.2488687783
0.0) (11 9547.5113122172 45.2488687783 0.0))
((0 . "LINE") (100 . "AcDbEntity") (8 . "ARCH") (62 . 7) (370 . 13) (100 . "AcDbLine") (10 10701.3574660633
3269.2307692308 0.0) (11 11809.9547511312 3269.2307692308 0.0))
((0 . "LINE") (100 . "AcDbEntity") (8 . "ARCH") (62 . 7) (370 . 13) (100 . "AcDbLine") (10 11809.9547511312
3269.2307692308 0.0) (11 11809.9547511312 3190.0452488688 0.0))
((0 . "LINE") (100 . "AcDbEntity") (8 . "ARCH") (62 . 7) (370 . 13) (100 . "AcDbLine") (10 11809.9547511312
3190.0452488688 0.0) (11 11787.3303167421 3190.0452488688 0.0))
((0 . "LINE") (100 . "AcDbEntity") (8 . "ARCH") (62 . 7) (370 . 13) (100 . "AcDbLine") (10 11787.3303167421
3190.0452488688 0.0) (11 10723.9819004525 3190.0452488688 0.0))
((0 . "LINE") (100 . "AcDbEntity") (8 . "ARCH") (62 . 7) (370 . 13) (100 . "AcDbLine") (10 10723.9819004525
3190.0452488688 0.0) (11 10701.3574660633 3190.0452488688 0.0))
((0 . "LINE") (100 . "AcDbEntity") (8 . "ARCH") (62 . 7) (370 . 13) (100 . "AcDbLine") (10 10701.3574660633
3190.0452488688 0.0) (11 10701.3574660633 3269.2307692308 0.0))
((0 . "LINE") (100 . "AcDbEntity") (8 . "ARCH") (62 . 7) (370 . 13) (100 . "AcDbLine") (10 10723.9819004525
3190.0452488688 0.0) (11 10791.8552036199 3122.1719457014 0.0))
((0 . "LINE") (100 . "AcDbEntity") (8 . "ARCH") (62 . 7) (370 . 13) (100 . "AcDbLine") (10 10791.8552036199
3122.1719457014 0.0) (11 10803.1674208145 3110.8597285068 0.0))
((0 . "LINE") (100 . "AcDbEntity") (8 . "ARCH") (62 . 7) (370 . 13) (100 . "AcDbLine") (10 10803.1674208145
3110.8597285068 0.0) (11 10814.4796380091 3076.9230769231 0.0))
((0 . "LINE") (100 . "AcDbEntity") (8 . "ARCH") (62 . 7) (370 . 13) (100 . "AcDbLine") (10 10814.4796380091
3076.9230769231 0.0) (11 11708.1447963801 3076.9230769231 0.0))
((0 . "LINE") (100 . "AcDbEntity") (8 . "ARCH") (62 . 7) (370 . 13) (100 . "AcDbLine") (10 11708.1447963801
3076.9230769231 0.0) (11 11719.4570135747 3110.8597285068 0.0))
((0 . "LINE") (100 . "AcDbEntity") (8 . "ARCH") (62 . 7) (370 . 13) (100 . "AcDbLine") (10 11719.4570135747
3110.8597285068 0.0) (11 11729.1532013575 3122.1719457014 0.0))
((0 . "LINE") (100 . "AcDbEntity") (8 . "ARCH") (62 . 7) (370 . 13) (100 . "AcDbLine") (10 11729.1532013575
3122.1719457014 0.0) (11 11787.3303167421 3190.0452488688 0.0))
((0 . "LINE") (100 . "AcDbEntity") (8 . "ARCH") (62 . 7) (370 . 13) (100 . "AcDbLine") (10 10791.8552036199
3122.1719457014 0.0) (11 11729.1532013575 3122.1719457014 0.0))
((0 . "LINE") (100 . "AcDbEntity") (8 . "ARCH") (62 . 7) (370 . 13) (100 . "AcDbLine") (10 11729.1532013575
3122.1719457014 0.0) (11 11730.7692307692 3122.1719457014 0.0))
((0 . "LINE") (100 . "AcDbEntity") (8 . "ARCH") (62 . 7) (370 . 13) (100 . "AcDbLine") (10 10452.4886877828
158.371040724 0.0) (11 12036.1990950226 158.371040724 0.0))
((0 . "LINE") (100 . "AcDbEntity") (8 . "ARCH") (62 . 7) (370 . 13) (100 . "AcDbLine") (10 10452.4886877828
101.8099547511 0.0) (11 12036.1990950226 101.8099547511 0.0))
((0 . "LINE") (100 . "AcDbEntity") (8 . "ARCH") (62 . 7) (370 . 13) (100 . "AcDbLine") (10 10452.4886877828
45.2488687783 0.0) (11 12036.1990950226 45.2488687783 0.0))
((0 . "LINE") (100 . "AcDbEntity") (8 . "ARCH") (62 . 7) (370 . 13) (100 . "AcDbLine") (10 2658.371040724
6832.5791855204 0.0) (11 2952.4886877828 6832.5791855204 0.0))
((0 . "LINE") (100 . "AcDbEntity") (8 . "ARCH") (62 . 7) (370 . 13) (100 . "AcDbLine") (10 2952.4886877828
6832.5791855204 0.0) (11 3710.407239819 6832.5791855204 0.0))
((0 . "LINE") (100 . "AcDbEntity") (8 . "ARCH") (62 . 7) (370 . 13) (100 . "AcDbLine") (10 3710.407239819
6832.5791855204 0.0) (11 4389.1402714932 6832.5791855204 0.0))
((0 . "LINE") (100 . "AcDbEntity") (8 . "ARCH") (62 . 7) (370 . 13) (100 . "AcDbLine") (10 4389.1402714932
6832.5791855204 0.0) (11 4389.1402714932 6764.7058823529 0.0))
((0 . "LINE") (100 . "AcDbEntity") (8 . "ARCH") (62 . 7) (370 . 13) (100 . "AcDbLine") (10 4389.1402714932
6764.7058823529 0.0) (11 4366.5158371041 6764.7058823529 0.0))
((0 . "LINE") (100 . "AcDbEntity") (8 . "ARCH") (62 . 7) (370 . 13) (100 . "AcDbLine") (10 4366.5158371041
6764.7058823529 0.0) (11 2680.9954751131 6764.7058823529 0.0))
((0 . "LINE") (100 . "AcDbEntity") (8 . "ARCH") (62 . 7) (370 . 13) (100 . "AcDbLine") (10 2680.9954751131
6764.7058823529 0.0) (11 2658.371040724 6764.7058823529 0.0))
((0 . "LINE") (100 . "AcDbEntity") (8 . "ARCH") (62 . 7) (370 . 13) (100 . "AcDbLine") (10 2658.371040724
6764.7058823529 0.0) (11 2658.371040724 6832.5791855204 0.0))
((0 . "LINE") (100 . "AcDbEntity") (8 . "ARCH") (62 . 7) (370 . 13) (100 . "AcDbLine") (10 2680.9954751131
6764.7058823529 0.0) (11 2726.2443438914 6696.8325791855 0.0))
((0 . "LINE") (100 . "AcDbEntity") (8 . "ARCH") (62 . 7) (370 . 13) (100 . "AcDbLine") (10 2726.2443438914
6696.8325791855 0.0) (11 2726.2443438914 6549.7737556561 0.0))
((0 . "LINE") (100 . "AcDbEntity") (8 . "ARCH") (62 . 7) (370 . 13) (100 . "AcDbLine") (10 2726.2443438914
6549.7737556561 0.0) (11 2726.2443438914 6481.9004524887 0.0))
((0 . "LINE") (100 . "AcDbEntity") (8 . "ARCH") (62 . 7) (370 . 13) (100 . "AcDbLine") (10 4276.0180995475
6481.9004524887 0.0) (11 4309.9547511312 6481.9004524887 0.0))
((0 . "LINE") (100 . "AcDbEntity") (8 . "ARCH") (62 . 7) (370 . 13) (100 . "AcDbLine") (10 4309.9547511312
6481.9004524887 0.0) (11 4309.9547511312 6549.7737556561 0.0))
((0 . "LINE") (100 . "AcDbEntity") (8 . "ARCH") (62 . 7) (370 . 13) (100 . "AcDbLine") (10 4309.9547511312
6549.7737556561 0.0) (11 4309.9547511312 6696.8325791855 0.0))
((0 . "LINE") (100 . "AcDbEntity") (8 . "ARCH") (62 . 7) (370 . 13) (100 . "AcDbLine") (10 4309.9547511312
6696.8325791855 0.0) (11 4366.5158371041 6764.7058823529 0.0))
((0 . "LINE") (100 . "AcDbEntity") (8 . "ARCH") (62 . 7) (370 . 13) (100 . "AcDbLine") (10 6504.5248868778
6832.5791855204 0.0) (11 7330.3167420814 6832.5791855204 0.0))
((0 . "LINE") (100 . "AcDbEntity") (8 . "ARCH") (62 . 7) (370 . 13) (100 . "AcDbLine") (10 7330.3167420814
6832.5791855204 0.0) (11 7714.9321266968 6832.5791855204 0.0))
((0 . "LINE") (100 . "AcDbEntity") (8 . "ARCH") (62 . 7) (370 . 13) (100 . "AcDbLine") (10 7714.9321266968
6832.5791855204 0.0) (11 8088.2352941176 6832.5791855204 0.0))
((0 . "LINE") (100 . "AcDbEntity") (8 . "ARCH") (62 . 7) (370 . 13) (100 . "AcDbLine") (10 8088.2352941176
6832.5791855204 0.0) (11 8088.2352941176 6764.7058823529 0.0))
((0 . "LINE") (100 . "AcDbEntity") (8 . "ARCH") (62 . 7) (370 . 13) (100 . "AcDbLine") (10 8088.2352941176
6764.7058823529 0.0) (11 8065.6108597285 6764.7058823529 0.0))
((0 . "LINE") (100 . "AcDbEntity") (8 . "ARCH") (62 . 7) (370 . 13) (100 . "AcDbLine") (10 8065.6108597285
6764.7058823529 0.0) (11 6527.149321267 6764.7058823529 0.0))
((0 . "LINE") (100 . "AcDbEntity") (8 . "ARCH") (62 . 7) (370 . 13) (100 . "AcDbLine") (10 6527.149321267
6764.7058823529 0.0) (11 6504.5248868778 6764.7058823529 0.0))
((0 . "LINE") (100 . "AcDbEntity") (8 . "ARCH") (62 . 7) (370 . 13) (100 . "AcDbLine") (10 6504.5248868778
6764.7058823529 0.0) (11 6504.5248868778 6832.5791855204 0.0))
((0 . "LINE") (100 . "AcDbEntity") (8 . "ARCH") (62 . 7) (370 . 13) (100 . "AcDbLine") (10 6527.149321267
6764.7058823529 0.0) (11 6572.3981900452 6696.8325791855 0.0))
((0 . "LINE") (100 . "AcDbEntity") (8 . "ARCH") (62 . 7) (370 . 13) (100 . "AcDbLine") (10 6572.3981900452
6696.8325791855 0.0) (11 6572.3981900452 6549.7737556561 0.0))
((0 . "LINE") (100 . "AcDbEntity") (8 . "ARCH") (62 . 7) (370 . 13) (100 . "AcDbLine") (10 6572.3981900452
6549.7737556561 0.0) (11 6572.3981900452 6481.9004524887 0.0))
((0 . "LINE") (100 . "AcDbEntity") (8 . "ARCH") (62 . 7) (370 . 13) (100 . "AcDbLine") (10 6572.3981900452
6481.9004524887 0.0) (11 6628.9592760181 6481.9004524887 0.0))
((0 . "LINE") (100 . "AcDbEntity") (8 . "ARCH") (62 . 7) (370 . 13) (100 . "AcDbLine") (10 7941.1764705882
6481.9004524887 0.0) (11 8009.0497737557 6481.9004524887 0.0))
((0 . "LINE") (100 . "AcDbEntity") (8 . "ARCH") (62 . 7) (370 . 13) (100 . "AcDbLine") (10 8009.0497737557
6481.9004524887 0.0) (11 8009.0497737557 6549.7737556561 0.0))
((0 . "LINE") (100 . "AcDbEntity") (8 . "ARCH") (62 . 7) (370 . 13) (100 . "AcDbLine") (10 8009.0497737557
6549.7737556561 0.0) (11 8009.0497737557 6696.8325791855 0.0))
((0 . "LINE") (100 . "AcDbEntity") (8 . "ARCH") (62 . 7) (370 . 13) (100 . "AcDbLine") (10 8009.0497737557
6696.8325791855 0.0) (11 8065.6108597285 6764.7058823529 0.0))
((0 . "LINE") (100 . "AcDbEntity") (8 . "ARCH") (62 . 7) (370 . 13) (100 . "AcDbLine") (10 11911.7647058824
6832.5791855204 0.0) (11 12149.3212669683 6832.5791855204 0.0))
((0 . "LINE") (100 . "AcDbEntity") (8 . "ARCH") (62 . 7) (370 . 13) (100 . "AcDbLine") (10 12149.3212669683
6832.5791855204 0.0) (11 12590.4977375566 6832.5791855204 0.0))
((0 . "LINE") (100 . "AcDbEntity") (8 . "ARCH") (62 . 7) (370 . 13) (100 . "AcDbLine") (10 12590.4977375566
6832.5791855204 0.0) (11 13518.0995475113 6832.5791855204 0.0))
((0 . "LINE") (100 . "AcDbEntity") (8 . "ARCH") (62 . 7) (370 . 13) (100 . "AcDbLine") (10 13518.0995475113
6832.5791855204 0.0) (11 13518.0995475113 6764.7058823529 0.0))
((0 . "LINE") (100 . "AcDbEntity") (8 . "ARCH") (62 . 7) (370 . 13) (100 . "AcDbLine") (10 13518.0995475113
6764.7058823529 0.0) (11 13495.4751131222 6764.7058823529 0.0))
((0 . "LINE") (100 . "AcDbEntity") (8 . "ARCH") (62 . 7) (370 . 13) (100 . "AcDbLine") (10 13495.4751131222
6764.7058823529 0.0) (11 11934.3891402715 6764.7058823529 0.0))
((0 . "LINE") (100 . "AcDbEntity") (8 . "ARCH") (62 . 7) (370 . 13) (100 . "AcDbLine") (10 11934.3891402715
6764.7058823529 0.0) (11 11911.7647058824 6764.7058823529 0.0))
((0 . "LINE") (100 . "AcDbEntity") (8 . "ARCH") (62 . 7) (370 . 13) (100 . "AcDbLine") (10 11911.7647058824
6764.7058823529 0.0) (11 11911.7647058824 6832.5791855204 0.0))
((0 . "LINE") (100 . "AcDbEntity") (8 . "ARCH") (62 . 7) (370 . 13) (100 . "AcDbLine") (10 11934.3891402715
6764.7058823529 0.0) (11 11979.6380090498 6696.8325791855 0.0))
((0 . "LINE") (100 . "AcDbEntity") (8 . "ARCH") (62 . 7) (370 . 13) (100 . "AcDbLine") (10 11979.6380090498
6696.8325791855 0.0) (11 11979.6380090498 6549.7737556561 0.0))
((0 . "LINE") (100 . "AcDbEntity") (8 . "ARCH") (62 . 7) (370 . 13) (100 . "AcDbLine") (10 11979.6380090498
6549.7737556561 0.0) (11 11979.6380090498 6481.9004524887 0.0))
((0 . "LINE") (100 . "AcDbEntity") (8 . "ARCH") (62 . 7) (370 . 13) (100 . "AcDbLine") (10 11979.6380090498
6481.9004524887 0.0) (11 12036.1990950226 6481.9004524887 0.0))
((0 . "LINE") (100 . "AcDbEntity") (8 . "ARCH") (62 . 7) (370 . 13) (100 . "AcDbLine") (10 13348.4162895928
6481.9004524887 0.0) (11 13438.9140271493 6481.9004524887 0.0))
((0 . "LINE") (100 . "AcDbEntity") (8 . "ARCH") (62 . 7) (370 . 13) (100 . "AcDbLine") (10 13438.9140271493
6481.9004524887 0.0) (11 13438.9140271493 6549.7737556561 0.0))
((0 . "LINE") (100 . "AcDbEntity") (8 . "ARCH") (62 . 7) (370 . 13) (100 . "AcDbLine") (10 13438.9140271493
6549.7737556561 0.0) (11 13438.9140271493 6696.8325791855 0.0))
((0 . "LINE") (100 . "AcDbEntity") (8 . "ARCH") (62 . 7) (370 . 13) (100 . "AcDbLine") (10 13438.9140271493
6696.8325791855 0.0) (11 13495.4751131222 6764.7058823529 0.0))
((0 . "LINE") (100 . "AcDbEntity") (8 . "ARCH") (62 . 7) (370 . 13) (100 . "AcDbLine") (10 15644.7963800905
6832.5791855204 0.0) (11 16334.8416289593 6832.5791855204 0.0))
((0 . "LINE") (100 . "AcDbEntity") (8 . "ARCH") (62 . 7) (370 . 13) (100 . "AcDbLine") (10 16334.8416289593
6832.5791855204 0.0) (11 17092.7601809955 6832.5791855204 0.0))
((0 . "LINE") (100 . "AcDbEntity") (8 . "ARCH") (62 . 7) (370 . 13) (100 . "AcDbLine") (10 17092.7601809955
6832.5791855204 0.0) (11 17409.5022624434 6832.5791855204 0.0))
((0 . "LINE") (100 . "AcDbEntity") (8 . "ARCH") (62 . 7) (370 . 13) (100 . "AcDbLine") (10 17409.5022624434
6832.5791855204 0.0) (11 17409.5022624434 6764.7058823529 0.0))
((0 . "LINE") (100 . "AcDbEntity") (8 . "ARCH") (62 . 7) (370 . 13) (100 . "AcDbLine") (10 17409.5022624434
6764.7058823529 0.0) (11 17386.8778280543 6764.7058823529 0.0))
((0 . "LINE") (100 . "AcDbEntity") (8 . "ARCH") (62 . 7) (370 . 13) (100 . "AcDbLine") (10 17386.8778280543
6764.7058823529 0.0) (11 15667.4208144796 6764.7058823529 0.0))
((0 . "LINE") (100 . "AcDbEntity") (8 . "ARCH") (62 . 7) (370 . 13) (100 . "AcDbLine") (10 15667.4208144796
6764.7058823529 0.0) (11 15644.7963800905 6764.7058823529 0.0))
((0 . "LINE") (100 . "AcDbEntity") (8 . "ARCH") (62 . 7) (370 . 13) (100 . "AcDbLine") (10 15644.7963800905
6764.7058823529 0.0) (11 15644.7963800905 6832.5791855204 0.0))
((0 . "LINE") (100 . "AcDbEntity") (8 . "ARCH") (62 . 7) (370 . 13) (100 . "AcDbLine") (10 15667.4208144796
6764.7058823529 0.0) (11 15712.6696832579 6696.8325791855 0.0))
((0 . "LINE") (100 . "AcDbEntity") (8 . "ARCH") (62 . 7) (370 . 13) (100 . "AcDbLine") (10 15712.6696832579
6696.8325791855 0.0) (11 15712.6696832579 6549.7737556561 0.0))
((0 . "LINE") (100 . "AcDbEntity") (8 . "ARCH") (62 . 7) (370 . 13) (100 . "AcDbLine") (10 15712.6696832579
6549.7737556561 0.0) (11 15712.6696832579 6481.9004524887 0.0))
((0 . "LINE") (100 . "AcDbEntity") (8 . "ARCH") (62 . 7) (370 . 13) (100 . "AcDbLine") (10 15712.6696832579
6481.9004524887 0.0) (11 15769.2307692308 6481.9004524887 0.0))
((0 . "LINE") (100 . "AcDbEntity") (8 . "ARCH") (62 . 7) (370 . 13) (100 . "AcDbLine") (10 17330.3167420814
6481.9004524887 0.0) (11 17330.3167420814 6549.7737556561 0.0))
((0 . "LINE") (100 . "AcDbEntity") (8 . "ARCH") (62 . 7) (370 . 13) (100 . "AcDbLine") (10 17330.3167420814
6549.7737556561 0.0) (11 17330.3167420814 6696.8325791855 0.0))
((0 . "LINE") (100 . "AcDbEntity") (8 . "ARCH") (62 . 7) (370 . 13) (100 . "AcDbLine") (10 17330.3167420814
6696.8325791855 0.0) (11 17386.8778280543 6764.7058823529 0.0))
((0 . "LINE") (100 . "AcDbEntity") (8 . "LOUVERS") (62 . 7) (370 . 13) (100 . "AcDbLine") (10 9106.334841629
6762.4547511312 0.0) (11 9377.8280542986 6762.4547511312 0.0))
((0 . "LINE") (100 . "AcDbEntity") (8 . "LOUVERS") (62 . 7) (370 . 13) (100 . "AcDbLine") (10 9106.334841629
6710.6787330317 0.0) (11 9402.9411764706 6710.6787330317 0.0))
((0 . "LINE") (100 . "AcDbEntity") (8 . "LOUVERS") (62 . 7) (370 . 13) (100 . "AcDbLine") (10 9106.334841629
6643.0995475113 0.0) (11 9468.3257918552 6643.0995475113 0.0))
((0 . "LINE") (100 . "AcDbEntity") (8 . "LOUVERS") (62 . 7) (370 . 13) (100 . "AcDbLine") (10 9106.334841629
6607.2624434389 0.0) (11 9479.6380090498 6607.2624434389 0.0))
((0 . "LINE") (100 . "AcDbEntity") (8 . "LOUVERS") (62 . 7) (370 . 13) (100 . "AcDbLine") (10 10633.4841628959
6761.8212669683 0.0) (11 10927.6018099548 6761.8212669683 0.0))
((0 . "LINE") (100 . "AcDbEntity") (8 . "LOUVERS") (62 . 7) (370 . 13) (100 . "AcDbLine") (10 10617.2087104072
6717.7488687783 0.0) (11 10927.6018099548 6717.7488687783 0.0))
((0 . "LINE") (100 . "AcDbEntity") (8 . "LOUVERS") (62 . 7) (370 . 13) (100 . "AcDbLine") (10 10579.9632352941
6687.9524886878 0.0) (11 10927.6018099548 6687.9524886878 0.0))
((0 . "LINE") (100 . "AcDbEntity") (8 . "LOUVERS") (62 . 7) (370 . 13) (100 . "AcDbLine") (10 10541.556561086
6641.3122171946 0.0) (11 10927.6018099548 6641.3122171946 0.0))
((0 . "LINE") (100 . "AcDbEntity") (8 . "LOUVERS") (62 . 7) (370 . 13) (100 . "AcDbLine") (10 10531.6742081448
6607.0701357466 0.0) (11 10927.6018099548 6607.0701357466 0.0))
((0 . "LINE") (100 . "AcDbEntity") (8 . "LOUVERS") (62 . 7) (370 . 13) (100 . "AcDbLine") (10 4140.2714932127
5531.6742081448 0.0) (11 4172.0475113122 5531.6742081448 0.0))
((0 . "LINE") (100 . "AcDbEntity") (8 . "LOUVERS") (62 . 7) (370 . 13) (100 . "AcDbLine") (10 4172.0475113122
5531.6742081448 0.0) (11 4174.2081447964 5531.6742081448 0.0))
((0 . "LINE") (100 . "AcDbEntity") (8 . "LOUVERS") (62 . 7) (370 . 13) (100 . "AcDbLine") (10 4671.9457013575
5531.6742081448 0.0) (11 4671.9457013575 5045.2488687783 0.0))
((0 . "LINE") (100 . "AcDbEntity") (8 . "LOUVERS") (62 . 7) (370 . 13) (100 . "AcDbLine") (10 4671.9457013575
5045.2488687783 0.0) (11 4671.9457013575 3800.9049773756 0.0))
((0 . "LINE") (100 . "AcDbEntity") (8 . "LOUVERS") (62 . 7) (370 . 13) (100 . "AcDbLine") (10 4671.9457013575
3800.9049773756 0.0) (11 4640.7918552036 3800.9049773756 0.0))
((0 . "LINE") (100 . "AcDbEntity") (8 . "LOUVERS") (62 . 7) (370 . 13) (100 . "AcDbLine") (10 4640.7918552036
3800.9049773756 0.0) (11 4578.9592760181 3800.9049773756 0.0))
((0 . "LINE") (100 . "AcDbEntity") (8 . "LOUVERS") (62 . 7) (370 . 13) (100 . "AcDbLine") (10 4578.9592760181
3800.9049773756 0.0) (11 4499.0384615385 3800.9049773756 0.0))
((0 . "LINE") (100 . "AcDbEntity") (8 . "LOUVERS") (62 . 7) (370 . 13) (100 . "AcDbLine") (10 4499.0384615385
3800.9049773756 0.0) (11 4460.6221719457 3800.9049773756 0.0))
((0 . "LINE") (100 . "AcDbEntity") (8 . "LOUVERS") (62 . 7) (370 . 13) (100 . "AcDbLine") (10 4460.6221719457
3800.9049773756 0.0) (11 4392.8959276018 3800.9049773756 0.0))
((0 . "LINE") (100 . "AcDbEntity") (8 . "LOUVERS") (62 . 7) (370 . 13) (100 . "AcDbLine") (10 4392.8959276018
3800.9049773756 0.0) (11 4331.0859728507 3800.9049773756 0.0))
((0 . "LINE") (100 . "AcDbEntity") (8 . "LOUVERS") (62 . 7) (370 . 13) (100 . "AcDbLine") (10 4331.0859728507
3800.9049773756 0.0) (11 4310.9502262443 3800.9049773756 0.0))
((0 . "LINE") (100 . "AcDbEntity") (8 . "LOUVERS") (62 . 7) (370 . 13) (100 . "AcDbLine") (10 4310.9502262443
3800.9049773756 0.0) (11 4252.1719457014 3800.9049773756 0.0))
((0 . "LINE") (100 . "AcDbEntity") (8 . "LOUVERS") (62 . 7) (370 . 13) (100 . "AcDbLine") (10 4252.1719457014
3800.9049773756 0.0) (11 4233.0656108597 3800.9049773756 0.0))
((0 . "LINE") (100 . "AcDbEntity") (8 . "LOUVERS") (62 . 7) (370 . 13) (100 . "AcDbLine") (10 4233.0656108597
3800.9049773756 0.0) (11 4172.0475113122 3800.9049773756 0.0))
((0 . "LINE") (100 . "AcDbEntity") (8 . "LOUVERS") (62 . 7) (370 . 13) (100 . "AcDbLine") (10 4172.0475113122
3800.9049773756 0.0) (11 4140.2714932127 3800.9049773756 0.0))
((0 . "LINE") (100 . "AcDbEntity") (8 . "LOUVERS") (62 . 7) (370 . 13) (100 . "AcDbLine") (10 4140.2714932127
3800.9049773756 0.0) (11 4140.2714932127 5531.6742081448 0.0))
((0 . "LINE") (100 . "AcDbEntity") (8 . "LOUVERS") (62 . 7) (370 . 13) (100 . "AcDbLine") (10 4172.0475113122
5531.6742081448 0.0) (11 4172.0475113122 3800.9049773756 0.0))
((0 . "LINE") (100 . "AcDbEntity") (8 . "LOUVERS") (62 . 7) (370 . 13) (100 . "AcDbLine") (10 4233.0656108597
5531.6742081448 0.0) (11 4233.0656108597 3800.9049773756 0.0))
((0 . "LINE") (100 . "AcDbEntity") (8 . "LOUVERS") (62 . 7) (370 . 13) (100 . "AcDbLine") (10 4252.1719457014
5531.6742081448 0.0) (11 4252.1719457014 3800.9049773756 0.0))
((0 . "LINE") (100 . "AcDbEntity") (8 . "LOUVERS") (62 . 7) (370 . 13) (100 . "AcDbLine") (10 4310.9502262443
5531.6742081448 0.0) (11 4310.9502262443 3800.9049773756 0.0))
((0 . "LINE") (100 . "AcDbEntity") (8 . "LOUVERS") (62 . 7) (370 . 13) (100 . "AcDbLine") (10 4331.0859728507
5531.6742081448 0.0) (11 4331.0859728507 3800.9049773756 0.0))
((0 . "LINE") (100 . "AcDbEntity") (8 . "LOUVERS") (62 . 7) (370 . 13) (100 . "AcDbLine") (10 4392.8959276018
5531.6742081448 0.0) (11 4392.8959276018 3800.9049773756 0.0))
((0 . "LINE") (100 . "AcDbEntity") (8 . "LOUVERS") (62 . 7) (370 . 13) (100 . "AcDbLine") (10 4460.6221719457
5531.6742081448 0.0) (11 4460.6221719457 3800.9049773756 0.0))
((0 . "LINE") (100 . "AcDbEntity") (8 . "LOUVERS") (62 . 7) (370 . 13) (100 . "AcDbLine") (10 4499.0384615385
5531.6742081448 0.0) (11 4499.0384615385 3800.9049773756 0.0))
((0 . "LINE") (100 . "AcDbEntity") (8 . "LOUVERS") (62 . 7) (370 . 13) (100 . "AcDbLine") (10 4578.9592760181
5531.6742081448 0.0) (11 4578.9592760181 3800.9049773756 0.0))
((0 . "LINE") (100 . "AcDbEntity") (8 . "LOUVERS") (62 . 7) (370 . 13) (100 . "AcDbLine") (10 4640.7918552036
5531.6742081448 0.0) (11 4640.7918552036 3800.9049773756 0.0))
((0 . "LINE") (100 . "AcDbEntity") (8 . "LOUVERS") (62 . 7) (370 . 13) (100 . "AcDbLine") (10 6674.2081447964
5531.6742081448 0.0) (11 6708.1447963801 5531.6742081448 0.0))
((0 . "LINE") (100 . "AcDbEntity") (8 . "LOUVERS") (62 . 7) (370 . 13) (100 . "AcDbLine") (10 6708.1447963801
5531.6742081448 0.0) (11 6708.1447963801 3800.9049773756 0.0))
((0 . "LINE") (100 . "AcDbEntity") (8 . "LOUVERS") (62 . 7) (370 . 13) (100 . "AcDbLine") (10 6708.1447963801
3800.9049773756 0.0) (11 6658.6312217195 3800.9049773756 0.0))
((0 . "LINE") (100 . "AcDbEntity") (8 . "LOUVERS") (62 . 7) (370 . 13) (100 . "AcDbLine") (10 6658.6312217195
3800.9049773756 0.0) (11 6582.5113122172 3800.9049773756 0.0))
((0 . "LINE") (100 . "AcDbEntity") (8 . "LOUVERS") (62 . 7) (370 . 13) (100 . "AcDbLine") (10 6582.5113122172
3800.9049773756 0.0) (11 6523.9932126697 3800.9049773756 0.0))
((0 . "LINE") (100 . "AcDbEntity") (8 . "LOUVERS") (62 . 7) (370 . 13) (100 . "AcDbLine") (10 6523.9932126697
3800.9049773756 0.0) (11 6508.2918552036 3800.9049773756 0.0))
((0 . "LINE") (100 . "AcDbEntity") (8 . "LOUVERS") (62 . 7) (370 . 13) (100 . "AcDbLine") (10 6508.2918552036
3800.9049773756 0.0) (11 6454.7737556561 3800.9049773756 0.0))
((0 . "LINE") (100 . "AcDbEntity") (8 . "LOUVERS") (62 . 7) (370 . 13) (100 . "AcDbLine") (10 6454.7737556561
3800.9049773756 0.0) (11 6374.4230769231 3800.9049773756 0.0))
((0 . "LINE") (100 . "AcDbEntity") (8 . "LOUVERS") (62 . 7) (370 . 13) (100 . "AcDbLine") (10 6374.4230769231
3800.9049773756 0.0) (11 6294.2194570136 3800.9049773756 0.0))
((0 . "LINE") (100 . "AcDbEntity") (8 . "LOUVERS") (62 . 7) (370 . 13) (100 . "AcDbLine") (10 6294.2194570136
3800.9049773756 0.0) (11 6234.2647058824 3800.9049773756 0.0))
((0 . "LINE") (100 . "AcDbEntity") (8 . "LOUVERS") (62 . 7) (370 . 13) (100 . "AcDbLine") (10 6234.2647058824
3800.9049773756 0.0) (11 6210.407239819 3800.9049773756 0.0))
((0 . "LINE") (100 . "AcDbEntity") (8 . "LOUVERS") (62 . 7) (370 . 13) (100 . "AcDbLine") (10 6210.407239819
3800.9049773756 0.0) (11 6210.407239819 5045.2488687783 0.0))
((0 . "LINE") (100 . "AcDbEntity") (8 . "LOUVERS") (62 . 7) (370 . 13) (100 . "AcDbLine") (10 6210.407239819
5045.2488687783 0.0) (11 6210.407239819 5531.6742081448 0.0))
((0 . "LINE") (100 . "AcDbEntity") (8 . "LOUVERS") (62 . 7) (370 . 13) (100 . "AcDbLine") (10 6234.2647058824
5531.6742081448 0.0) (11 6234.2647058824 3800.9049773756 0.0))
((0 . "LINE") (100 . "AcDbEntity") (8 . "LOUVERS") (62 . 7) (370 . 13) (100 . "AcDbLine") (10 6294.2194570136
5531.6742081448 0.0) (11 6294.2194570136 3800.9049773756 0.0))
((0 . "LINE") (100 . "AcDbEntity") (8 . "LOUVERS") (62 . 7) (370 . 13) (100 . "AcDbLine") (10 6374.4230769231
5531.6742081448 0.0) (11 6374.4230769231 3800.9049773756 0.0))
((0 . "LINE") (100 . "AcDbEntity") (8 . "LOUVERS") (62 . 7) (370 . 13) (100 . "AcDbLine") (10 6454.7737556561
5531.6742081448 0.0) (11 6454.7737556561 3800.9049773756 0.0))
((0 . "LINE") (100 . "AcDbEntity") (8 . "LOUVERS") (62 . 7) (370 . 13) (100 . "AcDbLine") (10 6508.2918552036
5531.6742081448 0.0) (11 6508.2918552036 3800.9049773756 0.0))
((0 . "LINE") (100 . "AcDbEntity") (8 . "LOUVERS") (62 . 7) (370 . 13) (100 . "AcDbLine") (10 6523.9932126697
5531.6742081448 0.0) (11 6523.9932126697 3800.9049773756 0.0))
((0 . "LINE") (100 . "AcDbEntity") (8 . "LOUVERS") (62 . 7) (370 . 13) (100 . "AcDbLine") (10 6582.5113122172
5531.6742081448 0.0) (11 6582.5113122172 3800.9049773756 0.0))
((0 . "LINE") (100 . "AcDbEntity") (8 . "LOUVERS") (62 . 7) (370 . 13) (100 . "AcDbLine") (10 6658.6312217195
5531.6742081448 0.0) (11 6658.6312217195 3800.9049773756 0.0))
((0 . "LINE") (100 . "AcDbEntity") (8 . "LOUVERS") (62 . 7) (370 . 13) (100 . "AcDbLine") (10 3235.2941176471
5712.6696832579 0.0) (11 3285.8031674208 5712.6696832579 0.0))
((0 . "LINE") (100 . "AcDbEntity") (8 . "LOUVERS") (62 . 7) (370 . 13) (100 . "AcDbLine") (10 3285.8031674208
5712.6696832579 0.0) (11 3315.9615384615 5712.6696832579 0.0))
((0 . "LINE") (100 . "AcDbEntity") (8 . "LOUVERS") (62 . 7) (370 . 13) (100 . "AcDbLine") (10 3315.9615384615
5712.6696832579 0.0) (11 3362.0814479638 5712.6696832579 0.0))
((0 . "LINE") (100 . "AcDbEntity") (8 . "LOUVERS") (62 . 7) (370 . 13) (100 . "AcDbLine") (10 3362.0814479638
5712.6696832579 0.0) (11 3390.8823529412 5712.6696832579 0.0))
((0 . "LINE") (100 . "AcDbEntity") (8 . "LOUVERS") (62 . 7) (370 . 13) (100 . "AcDbLine") (10 3390.8823529412
5712.6696832579 0.0) (11 3440.7126696833 5712.6696832579 0.0))
((0 . "LINE") (100 . "AcDbEntity") (8 . "LOUVERS") (62 . 7) (370 . 13) (100 . "AcDbLine") (10 3440.7126696833
5712.6696832579 0.0) (11 3507.0701357466 5712.6696832579 0.0))
((0 . "LINE") (100 . "AcDbEntity") (8 . "LOUVERS") (62 . 7) (370 . 13) (100 . "AcDbLine") (10 3507.0701357466
5712.6696832579 0.0) (11 3526.1538461538 5712.6696832579 0.0))
((0 . "LINE") (100 . "AcDbEntity") (8 . "LOUVERS") (62 . 7) (370 . 13) (100 . "AcDbLine") (10 3526.1538461538
5712.6696832579 0.0) (11 3573.5520361991 5712.6696832579 0.0))
((0 . "LINE") (100 . "AcDbEntity") (8 . "LOUVERS") (62 . 7) (370 . 13) (100 . "AcDbLine") (10 3573.5520361991
5712.6696832579 0.0) (11 3643.2352941176 5712.6696832579 0.0))
((0 . "LINE") (100 . "AcDbEntity") (8 . "LOUVERS") (62 . 7) (370 . 13) (100 . "AcDbLine") (10 3643.2352941176
5712.6696832579 0.0) (11 3663.9819004525 5712.6696832579 0.0))
((0 . "LINE") (100 . "AcDbEntity") (8 . "LOUVERS") (62 . 7) (370 . 13) (100 . "AcDbLine") (10 3663.9819004525
5712.6696832579 0.0) (11 3712.1380090498 5712.6696832579 0.0))
((0 . "LINE") (100 . "AcDbEntity") (8 . "LOUVERS") (62 . 7) (370 . 13) (100 . "AcDbLine") (10 3712.1380090498
5712.6696832579 0.0) (11 3739.8076923077 5712.6696832579 0.0))
((0 . "LINE") (100 . "AcDbEntity") (8 . "LOUVERS") (62 . 7) (370 . 13) (100 . "AcDbLine") (10 3739.8076923077
5712.6696832579 0.0) (11 3791.4705882353 5712.6696832579 0.0))
((0 . "LINE") (100 . "AcDbEntity") (8 . "LOUVERS") (62 . 7) (370 . 13) (100 . "AcDbLine") (10 3791.4705882353
5712.6696832579 0.0) (11 3800.9049773756 5712.6696832579 0.0))
((0 . "LINE") (100 . "AcDbEntity") (8 . "LOUVERS") (62 . 7) (370 . 13) (100 . "AcDbLine") (10 3800.9049773756
5712.6696832579 0.0) (11 3800.9049773756 5610.8597285068 0.0))
((0 . "LINE") (100 . "AcDbEntity") (8 . "LOUVERS") (62 . 7) (370 . 13) (100 . "AcDbLine") (10 3800.9049773756
5610.8597285068 0.0) (11 3800.9049773756 3800.9049773756 0.0))
((0 . "LINE") (100 . "AcDbEntity") (8 . "LOUVERS") (62 . 7) (370 . 13) (100 . "AcDbLine") (10 3800.9049773756
3800.9049773756 0.0) (11 3791.4705882353 3800.9049773756 0.0))
((0 . "LINE") (100 . "AcDbEntity") (8 . "LOUVERS") (62 . 7) (370 . 13) (100 . "AcDbLine") (10 3791.4705882353
3800.9049773756 0.0) (11 3739.8076923077 3800.9049773756 0.0))
((0 . "LINE") (100 . "AcDbEntity") (8 . "LOUVERS") (62 . 7) (370 . 13) (100 . "AcDbLine") (10 3739.8076923077
3800.9049773756 0.0) (11 3712.1380090498 3800.9049773756 0.0))
((0 . "LINE") (100 . "AcDbEntity") (8 . "LOUVERS") (62 . 7) (370 . 13) (100 . "AcDbLine") (10 3712.1380090498
3800.9049773756 0.0) (11 3663.9819004525 3800.9049773756 0.0))
((0 . "LINE") (100 . "AcDbEntity") (8 . "LOUVERS") (62 . 7) (370 . 13) (100 . "AcDbLine") (10 3663.9819004525
3800.9049773756 0.0) (11 3643.2352941176 3800.9049773756 0.0))
((0 . "LINE") (100 . "AcDbEntity") (8 . "LOUVERS") (62 . 7) (370 . 13) (100 . "AcDbLine") (10 3643.2352941176
3800.9049773756 0.0) (11 3573.5520361991 3800.9049773756 0.0))
((0 . "LINE") (100 . "AcDbEntity") (8 . "LOUVERS") (62 . 7) (370 . 13) (100 . "AcDbLine") (10 3573.5520361991
3800.9049773756 0.0) (11 3526.1538461538 3800.9049773756 0.0))
((0 . "LINE") (100 . "AcDbEntity") (8 . "LOUVERS") (62 . 7) (370 . 13) (100 . "AcDbLine") (10 3526.1538461538
3800.9049773756 0.0) (11 3507.0701357466 3800.9049773756 0.0))
((0 . "LINE") (100 . "AcDbEntity") (8 . "LOUVERS") (62 . 7) (370 . 13) (100 . "AcDbLine") (10 3507.0701357466
3800.9049773756 0.0) (11 3440.7126696833 3800.9049773756 0.0))
((0 . "LINE") (100 . "AcDbEntity") (8 . "LOUVERS") (62 . 7) (370 . 13) (100 . "AcDbLine") (10 3440.7126696833
3800.9049773756 0.0) (11 3390.8823529412 3800.9049773756 0.0))
((0 . "LINE") (100 . "AcDbEntity") (8 . "LOUVERS") (62 . 7) (370 . 13) (100 . "AcDbLine") (10 3390.8823529412
3800.9049773756 0.0) (11 3362.0814479638 3800.9049773756 0.0))
((0 . "LINE") (100 . "AcDbEntity") (8 . "LOUVERS") (62 . 7) (370 . 13) (100 . "AcDbLine") (10 3362.0814479638
3800.9049773756 0.0) (11 3315.9615384615 3800.9049773756 0.0))
((0 . "LINE") (100 . "AcDbEntity") (8 . "LOUVERS") (62 . 7) (370 . 13) (100 . "AcDbLine") (10 3315.9615384615
3800.9049773756 0.0) (11 3285.8031674208 3800.9049773756 0.0))
((0 . "LINE") (100 . "AcDbEntity") (8 . "LOUVERS") (62 . 7) (370 . 13) (100 . "AcDbLine") (10 3285.8031674208
3800.9049773756 0.0) (11 3235.2941176471 3800.9049773756 0.0))
((0 . "LINE") (100 . "AcDbEntity") (8 . "LOUVERS") (62 . 7) (370 . 13) (100 . "AcDbLine") (10 3235.2941176471
3800.9049773756 0.0) (11 3235.2941176471 5610.8597285068 0.0))
((0 . "LINE") (100 . "AcDbEntity") (8 . "LOUVERS") (62 . 7) (370 . 13) (100 . "AcDbLine") (10 3235.2941176471
5610.8597285068 0.0) (11 3235.2941176471 5712.6696832579 0.0))
((0 . "LINE") (100 . "AcDbEntity") (8 . "LOUVERS") (62 . 7) (370 . 13) (100 . "AcDbLine") (10 3285.8031674208
5712.6696832579 0.0) (11 3285.8031674208 5610.8597285068 0.0))
((0 . "LINE") (100 . "AcDbEntity") (8 . "LOUVERS") (62 . 7) (370 . 13) (100 . "AcDbLine") (10 3285.8031674208
5610.8597285068 0.0) (11 3285.8031674208 3800.9049773756 0.0))
((0 . "LINE") (100 . "AcDbEntity") (8 . "LOUVERS") (62 . 7) (370 . 13) (100 . "AcDbLine") (10 3315.9615384615
5712.6696832579 0.0) (11 3315.9615384615 5610.8597285068 0.0))
((0 . "LINE") (100 . "AcDbEntity") (8 . "LOUVERS") (62 . 7) (370 . 13) (100 . "AcDbLine") (10 3315.9615384615
5610.8597285068 0.0) (11 3315.9615384615 3800.9049773756 0.0))
((0 . "LINE") (100 . "AcDbEntity") (8 . "LOUVERS") (62 . 7) (370 . 13) (100 . "AcDbLine") (10 3362.0814479638
5712.6696832579 0.0) (11 3362.0814479638 5610.8597285068 0.0))
((0 . "LINE") (100 . "AcDbEntity") (8 . "LOUVERS") (62 . 7) (370 . 13) (100 . "AcDbLine") (10 3362.0814479638
5610.8597285068 0.0) (11 3362.0814479638 3800.9049773756 0.0))
((0 . "LINE") (100 . "AcDbEntity") (8 . "LOUVERS") (62 . 7) (370 . 13) (100 . "AcDbLine") (10 3390.8823529412
5712.6696832579 0.0) (11 3390.8823529412 5610.8597285068 0.0))
((0 . "LINE") (100 . "AcDbEntity") (8 . "LOUVERS") (62 . 7) (370 . 13) (100 . "AcDbLine") (10 3390.8823529412
5610.8597285068 0.0) (11 3390.8823529412 3800.9049773756 0.0))
((0 . "LINE") (100 . "AcDbEntity") (8 . "LOUVERS") (62 . 7) (370 . 13) (100 . "AcDbLine") (10 3440.7126696833
5712.6696832579 0.0) (11 3440.7126696833 5610.8597285068 0.0))
((0 . "LINE") (100 . "AcDbEntity") (8 . "LOUVERS") (62 . 7) (370 . 13) (100 . "AcDbLine") (10 3440.7126696833
5610.8597285068 0.0) (11 3440.7126696833 3800.9049773756 0.0))
((0 . "LINE") (100 . "AcDbEntity") (8 . "LOUVERS") (62 . 7) (370 . 13) (100 . "AcDbLine") (10 3507.0701357466
5712.6696832579 0.0) (11 3507.0701357466 5610.8597285068 0.0))
((0 . "LINE") (100 . "AcDbEntity") (8 . "LOUVERS") (62 . 7) (370 . 13) (100 . "AcDbLine") (10 3507.0701357466
5610.8597285068 0.0) (11 3507.0701357466 3800.9049773756 0.0))
((0 . "LINE") (100 . "AcDbEntity") (8 . "LOUVERS") (62 . 7) (370 . 13) (100 . "AcDbLine") (10 3526.1538461538
5712.6696832579 0.0) (11 3526.1538461538 5610.8597285068 0.0))
((0 . "LINE") (100 . "AcDbEntity") (8 . "LOUVERS") (62 . 7) (370 . 13) (100 . "AcDbLine") (10 3526.1538461538
5610.8597285068 0.0) (11 3526.1538461538 3800.9049773756 0.0))
((0 . "LINE") (100 . "AcDbEntity") (8 . "LOUVERS") (62 . 7) (370 . 13) (100 . "AcDbLine") (10 3573.5520361991
5712.6696832579 0.0) (11 3573.5520361991 5610.8597285068 0.0))
((0 . "LINE") (100 . "AcDbEntity") (8 . "LOUVERS") (62 . 7) (370 . 13) (100 . "AcDbLine") (10 3573.5520361991
5610.8597285068 0.0) (11 3573.5520361991 3800.9049773756 0.0))
((0 . "LINE") (100 . "AcDbEntity") (8 . "LOUVERS") (62 . 7) (370 . 13) (100 . "AcDbLine") (10 3643.2352941176
5712.6696832579 0.0) (11 3643.2352941176 5610.8597285068 0.0))
((0 . "LINE") (100 . "AcDbEntity") (8 . "LOUVERS") (62 . 7) (370 . 13) (100 . "AcDbLine") (10 3643.2352941176
5610.8597285068 0.0) (11 3643.2352941176 3800.9049773756 0.0))
((0 . "LINE") (100 . "AcDbEntity") (8 . "LOUVERS") (62 . 7) (370 . 13) (100 . "AcDbLine") (10 3663.9819004525
5712.6696832579 0.0) (11 3663.9819004525 5610.8597285068 0.0))
((0 . "LINE") (100 . "AcDbEntity") (8 . "LOUVERS") (62 . 7) (370 . 13) (100 . "AcDbLine") (10 3663.9819004525
5610.8597285068 0.0) (11 3663.9819004525 3800.9049773756 0.0))
((0 . "LINE") (100 . "AcDbEntity") (8 . "LOUVERS") (62 . 7) (370 . 13) (100 . "AcDbLine") (10 3712.1380090498
5712.6696832579 0.0) (11 3712.1380090498 5610.8597285068 0.0))
((0 . "LINE") (100 . "AcDbEntity") (8 . "LOUVERS") (62 . 7) (370 . 13) (100 . "AcDbLine") (10 3712.1380090498
5610.8597285068 0.0) (11 3712.1380090498 3800.9049773756 0.0))
((0 . "LINE") (100 . "AcDbEntity") (8 . "LOUVERS") (62 . 7) (370 . 13) (100 . "AcDbLine") (10 3739.8076923077
5712.6696832579 0.0) (11 3739.8076923077 5610.8597285068 0.0))
((0 . "LINE") (100 . "AcDbEntity") (8 . "LOUVERS") (62 . 7) (370 . 13) (100 . "AcDbLine") (10 3739.8076923077
5610.8597285068 0.0) (11 3739.8076923077 3800.9049773756 0.0))
((0 . "LINE") (100 . "AcDbEntity") (8 . "LOUVERS") (62 . 7) (370 . 13) (100 . "AcDbLine") (10 3791.4705882353
5712.6696832579 0.0) (11 3791.4705882353 5610.8597285068 0.0))
((0 . "LINE") (100 . "AcDbEntity") (8 . "LOUVERS") (62 . 7) (370 . 13) (100 . "AcDbLine") (10 3791.4705882353
5610.8597285068 0.0) (11 3791.4705882353 3800.9049773756 0.0))
((0 . "LINE") (100 . "AcDbEntity") (8 . "LOUVERS") (62 . 7) (370 . 13) (100 . "AcDbLine") (10 7047.5113122172
5712.6696832579 0.0) (11 7096.7647058824 5712.6696832579 0.0))
((0 . "LINE") (100 . "AcDbEntity") (8 . "LOUVERS") (62 . 7) (370 . 13) (100 . "AcDbLine") (10 7096.7647058824
5712.6696832579 0.0) (11 7127.8959276018 5712.6696832579 0.0))
((0 . "LINE") (100 . "AcDbEntity") (8 . "LOUVERS") (62 . 7) (370 . 13) (100 . "AcDbLine") (10 7127.8959276018
5712.6696832579 0.0) (11 7172.2058823529 5712.6696832579 0.0))
((0 . "LINE") (100 . "AcDbEntity") (8 . "LOUVERS") (62 . 7) (370 . 13) (100 . "AcDbLine") (10 7172.2058823529
5712.6696832579 0.0) (11 7202.0701357466 5712.6696832579 0.0))
((0 . "LINE") (100 . "AcDbEntity") (8 . "LOUVERS") (62 . 7) (370 . 13) (100 . "AcDbLine") (10 7202.0701357466
5712.6696832579 0.0) (11 7246.0972850679 5712.6696832579 0.0))
((0 . "LINE") (100 . "AcDbEntity") (8 . "LOUVERS") (62 . 7) (370 . 13) (100 . "AcDbLine") (10 7246.0972850679
5712.6696832579 0.0) (11 7273.778280543 5712.6696832579 0.0))
((0 . "LINE") (100 . "AcDbEntity") (8 . "LOUVERS") (62 . 7) (370 . 13) (100 . "AcDbLine") (10 7273.778280543
5712.6696832579 0.0) (11 7322.4321266968 5712.6696832579 0.0))
((0 . "LINE") (100 . "AcDbEntity") (8 . "LOUVERS") (62 . 7) (370 . 13) (100 . "AcDbLine") (10 7322.4321266968
5712.6696832579 0.0) (11 7349.9321266968 5712.6696832579 0.0))
((0 . "LINE") (100 . "AcDbEntity") (8 . "LOUVERS") (62 . 7) (370 . 13) (100 . "AcDbLine") (10 7349.9321266968
5712.6696832579 0.0) (11 7393.7330316742 5712.6696832579 0.0))
((0 . "LINE") (100 . "AcDbEntity") (8 . "LOUVERS") (62 . 7) (370 . 13) (100 . "AcDbLine") (10 7393.7330316742
5712.6696832579 0.0) (11 7424.4909502262 5712.6696832579 0.0))
((0 . "LINE") (100 . "AcDbEntity") (8 . "LOUVERS") (62 . 7) (370 . 13) (100 . "AcDbLine") (10 7424.4909502262
5712.6696832579 0.0) (11 7463.6425339367 5712.6696832579 0.0))
((0 . "LINE") (100 . "AcDbEntity") (8 . "LOUVERS") (62 . 7) (370 . 13) (100 . "AcDbLine") (10 7463.6425339367
5712.6696832579 0.0) (11 7501.3800904977 5712.6696832579 0.0))
((0 . "LINE") (100 . "AcDbEntity") (8 . "LOUVERS") (62 . 7) (370 . 13) (100 . "AcDbLine") (10 7501.3800904977
5712.6696832579 0.0) (11 7529.7171945701 5712.6696832579 0.0))
((0 . "LINE") (100 . "AcDbEntity") (8 . "LOUVERS") (62 . 7) (370 . 13) (100 . "AcDbLine") (10 7529.7171945701
5712.6696832579 0.0) (11 7579.185520362 5712.6696832579 0.0))
((0 . "LINE") (100 . "AcDbEntity") (8 . "LOUVERS") (62 . 7) (370 . 13) (100 . "AcDbLine") (10 7579.185520362
5712.6696832579 0.0) (11 7579.185520362 5610.8597285068 0.0))
((0 . "LINE") (100 . "AcDbEntity") (8 . "LOUVERS") (62 . 7) (370 . 13) (100 . "AcDbLine") (10 7579.185520362
5610.8597285068 0.0) (11 7579.185520362 3800.9049773756 0.0))
((0 . "LINE") (100 . "AcDbEntity") (8 . "LOUVERS") (62 . 7) (370 . 13) (100 . "AcDbLine") (10 7579.185520362
3800.9049773756 0.0) (11 7529.7171945701 3800.9049773756 0.0))
((0 . "LINE") (100 . "AcDbEntity") (8 . "LOUVERS") (62 . 7) (370 . 13) (100 . "AcDbLine") (10 7529.7171945701
3800.9049773756 0.0) (11 7501.3800904977 3800.9049773756 0.0))
((0 . "LINE") (100 . "AcDbEntity") (8 . "LOUVERS") (62 . 7) (370 . 13) (100 . "AcDbLine") (10 7501.3800904977
3800.9049773756 0.0) (11 7463.6425339367 3800.9049773756 0.0))
((0 . "LINE") (100 . "AcDbEntity") (8 . "LOUVERS") (62 . 7) (370 . 13) (100 . "AcDbLine") (10 7463.6425339367
3800.9049773756 0.0) (11 7424.4909502262 3800.9049773756 0.0))
((0 . "LINE") (100 . "AcDbEntity") (8 . "LOUVERS") (62 . 7) (370 . 13) (100 . "AcDbLine") (10 7424.4909502262
3800.9049773756 0.0) (11 7393.7330316742 3800.9049773756 0.0))
((0 . "LINE") (100 . "AcDbEntity") (8 . "LOUVERS") (62 . 7) (370 . 13) (100 . "AcDbLine") (10 7393.7330316742
3800.9049773756 0.0) (11 7349.9321266968 3800.9049773756 0.0))
((0 . "LINE") (100 . "AcDbEntity") (8 . "LOUVERS") (62 . 7) (370 . 13) (100 . "AcDbLine") (10 7349.9321266968
3800.9049773756 0.0) (11 7322.4321266968 3800.9049773756 0.0))
((0 . "LINE") (100 . "AcDbEntity") (8 . "LOUVERS") (62 . 7) (370 . 13) (100 . "AcDbLine") (10 7322.4321266968
3800.9049773756 0.0) (11 7273.778280543 3800.9049773756 0.0))
((0 . "LINE") (100 . "AcDbEntity") (8 . "LOUVERS") (62 . 7) (370 . 13) (100 . "AcDbLine") (10 7273.778280543
3800.9049773756 0.0) (11 7246.0972850679 3800.9049773756 0.0))
((0 . "LINE") (100 . "AcDbEntity") (8 . "LOUVERS") (62 . 7) (370 . 13) (100 . "AcDbLine") (10 7246.0972850679
3800.9049773756 0.0) (11 7202.0701357466 3800.9049773756 0.0))
((0 . "LINE") (100 . "AcDbEntity") (8 . "LOUVERS") (62 . 7) (370 . 13) (100 . "AcDbLine") (10 7202.0701357466
3800.9049773756 0.0) (11 7172.2058823529 3800.9049773756 0.0))
((0 . "LINE") (100 . "AcDbEntity") (8 . "LOUVERS") (62 . 7) (370 . 13) (100 . "AcDbLine") (10 7172.2058823529
3800.9049773756 0.0) (11 7127.8959276018 3800.9049773756 0.0))
((0 . "LINE") (100 . "AcDbEntity") (8 . "LOUVERS") (62 . 7) (370 . 13) (100 . "AcDbLine") (10 7127.8959276018
3800.9049773756 0.0) (11 7096.7647058824 3800.9049773756 0.0))
((0 . "LINE") (100 . "AcDbEntity") (8 . "LOUVERS") (62 . 7) (370 . 13) (100 . "AcDbLine") (10 7096.7647058824
3800.9049773756 0.0) (11 7047.5113122172 3800.9049773756 0.0))
((0 . "LINE") (100 . "AcDbEntity") (8 . "LOUVERS") (62 . 7) (370 . 13) (100 . "AcDbLine") (10 7047.5113122172
3800.9049773756 0.0) (11 7047.5113122172 5610.8597285068 0.0))
((0 . "LINE") (100 . "AcDbEntity") (8 . "LOUVERS") (62 . 7) (370 . 13) (100 . "AcDbLine") (10 7047.5113122172
5610.8597285068 0.0) (11 7047.5113122172 5712.6696832579 0.0))
((0 . "LINE") (100 . "AcDbEntity") (8 . "LOUVERS") (62 . 7) (370 . 13) (100 . "AcDbLine") (10 7096.7647058824
5712.6696832579 0.0) (11 7096.7647058824 5610.8597285068 0.0))
((0 . "LINE") (100 . "AcDbEntity") (8 . "LOUVERS") (62 . 7) (370 . 13) (100 . "AcDbLine") (10 7096.7647058824
5610.8597285068 0.0) (11 7096.7647058824 3800.9049773756 0.0))
((0 . "LINE") (100 . "AcDbEntity") (8 . "LOUVERS") (62 . 7) (370 . 13) (100 . "AcDbLine") (10 7127.8959276018
5712.6696832579 0.0) (11 7127.8959276018 5610.8597285068 0.0))
((0 . "LINE") (100 . "AcDbEntity") (8 . "LOUVERS") (62 . 7) (370 . 13) (100 . "AcDbLine") (10 7127.8959276018
5610.8597285068 0.0) (11 7127.8959276018 3800.9049773756 0.0))
((0 . "LINE") (100 . "AcDbEntity") (8 . "LOUVERS") (62 . 7) (370 . 13) (100 . "AcDbLine") (10 7172.2058823529
5712.6696832579 0.0) (11 7172.2058823529 5610.8597285068 0.0))
((0 . "LINE") (100 . "AcDbEntity") (8 . "LOUVERS") (62 . 7) (370 . 13) (100 . "AcDbLine") (10 7172.2058823529
5610.8597285068 0.0) (11 7172.2058823529 3800.9049773756 0.0))
((0 . "LINE") (100 . "AcDbEntity") (8 . "LOUVERS") (62 . 7) (370 . 13) (100 . "AcDbLine") (10 7202.0701357466
5712.6696832579 0.0) (11 7202.0701357466 5610.8597285068 0.0))
((0 . "LINE") (100 . "AcDbEntity") (8 . "LOUVERS") (62 . 7) (370 . 13) (100 . "AcDbLine") (10 7202.0701357466
5610.8597285068 0.0) (11 7202.0701357466 3800.9049773756 0.0))
((0 . "LINE") (100 . "AcDbEntity") (8 . "LOUVERS") (62 . 7) (370 . 13) (100 . "AcDbLine") (10 7246.0972850679
5712.6696832579 0.0) (11 7246.0972850679 5610.8597285068 0.0))
((0 . "LINE") (100 . "AcDbEntity") (8 . "LOUVERS") (62 . 7) (370 . 13) (100 . "AcDbLine") (10 7246.0972850679
5610.8597285068 0.0) (11 7246.0972850679 3800.9049773756 0.0))
((0 . "LINE") (100 . "AcDbEntity") (8 . "LOUVERS") (62 . 7) (370 . 13) (100 . "AcDbLine") (10 7273.778280543
5712.6696832579 0.0) (11 7273.778280543 5610.8597285068 0.0))
((0 . "LINE") (100 . "AcDbEntity") (8 . "LOUVERS") (62 . 7) (370 . 13) (100 . "AcDbLine") (10 7273.778280543
5610.8597285068 0.0) (11 7273.778280543 3800.9049773756 0.0))
((0 . "LINE") (100 . "AcDbEntity") (8 . "LOUVERS") (62 . 7) (370 . 13) (100 . "AcDbLine") (10 7322.4321266968
5712.6696832579 0.0) (11 7322.4321266968 5610.8597285068 0.0))
((0 . "LINE") (100 . "AcDbEntity") (8 . "LOUVERS") (62 . 7) (370 . 13) (100 . "AcDbLine") (10 7322.4321266968
5610.8597285068 0.0) (11 7322.4321266968 3800.9049773756 0.0))
((0 . "LINE") (100 . "AcDbEntity") (8 . "LOUVERS") (62 . 7) (370 . 13) (100 . "AcDbLine") (10 7349.9321266968
5712.6696832579 0.0) (11 7349.9321266968 5610.8597285068 0.0))
((0 . "LINE") (100 . "AcDbEntity") (8 . "LOUVERS") (62 . 7) (370 . 13) (100 . "AcDbLine") (10 7349.9321266968
5610.8597285068 0.0) (11 7349.9321266968 3800.9049773756 0.0))
((0 . "LINE") (100 . "AcDbEntity") (8 . "LOUVERS") (62 . 7) (370 . 13) (100 . "AcDbLine") (10 7393.7330316742
5712.6696832579 0.0) (11 7393.7330316742 5610.8597285068 0.0))
((0 . "LINE") (100 . "AcDbEntity") (8 . "LOUVERS") (62 . 7) (370 . 13) (100 . "AcDbLine") (10 7393.7330316742
5610.8597285068 0.0) (11 7393.7330316742 3800.9049773756 0.0))
((0 . "LINE") (100 . "AcDbEntity") (8 . "LOUVERS") (62 . 7) (370 . 13) (100 . "AcDbLine") (10 7424.4909502262
5712.6696832579 0.0) (11 7424.4909502262 5610.8597285068 0.0))
((0 . "LINE") (100 . "AcDbEntity") (8 . "LOUVERS") (62 . 7) (370 . 13) (100 . "AcDbLine") (10 7424.4909502262
5610.8597285068 0.0) (11 7424.4909502262 3800.9049773756 0.0))
((0 . "LINE") (100 . "AcDbEntity") (8 . "LOUVERS") (62 . 7) (370 . 13) (100 . "AcDbLine") (10 7463.6425339367
5712.6696832579 0.0) (11 7463.6425339367 5610.8597285068 0.0))
((0 . "LINE") (100 . "AcDbEntity") (8 . "LOUVERS") (62 . 7) (370 . 13) (100 . "AcDbLine") (10 7463.6425339367
5610.8597285068 0.0) (11 7463.6425339367 3800.9049773756 0.0))
((0 . "LINE") (100 . "AcDbEntity") (8 . "LOUVERS") (62 . 7) (370 . 13) (100 . "AcDbLine") (10 7501.3800904977
5712.6696832579 0.0) (11 7501.3800904977 5610.8597285068 0.0))
((0 . "LINE") (100 . "AcDbEntity") (8 . "LOUVERS") (62 . 7) (370 . 13) (100 . "AcDbLine") (10 7501.3800904977
5610.8597285068 0.0) (11 7501.3800904977 3800.9049773756 0.0))
((0 . "LINE") (100 . "AcDbEntity") (8 . "LOUVERS") (62 . 7) (370 . 13) (100 . "AcDbLine") (10 7529.7171945701
5712.6696832579 0.0) (11 7529.7171945701 5610.8597285068 0.0))
((0 . "LINE") (100 . "AcDbEntity") (8 . "LOUVERS") (62 . 7) (370 . 13) (100 . "AcDbLine") (10 7529.7171945701
5610.8597285068 0.0) (11 7529.7171945701 3800.9049773756 0.0))
((0 . "LINE") (100 . "AcDbEntity") (8 . "LOUVERS") (62 . 7) (370 . 13) (100 . "AcDbLine") (10 4061.0859728507
3212.6696832579 0.0) (11 4105.2036199095 3212.6696832579 0.0))
((0 . "LINE") (100 . "AcDbEntity") (8 . "LOUVERS") (62 . 7) (370 . 13) (100 . "AcDbLine") (10 4105.2036199095
3212.6696832579 0.0) (11 4134.8981900452 3212.6696832579 0.0))
((0 . "LINE") (100 . "AcDbEntity") (8 . "LOUVERS") (62 . 7) (370 . 13) (100 . "AcDbLine") (10 4134.8981900452
3212.6696832579 0.0) (11 4174.5588235294 3212.6696832579 0.0))
((0 . "LINE") (100 . "AcDbEntity") (8 . "LOUVERS") (62 . 7) (370 . 13) (100 . "AcDbLine") (10 4174.5588235294
3212.6696832579 0.0) (11 4207.9411764706 3212.6696832579 0.0))
((0 . "LINE") (100 . "AcDbEntity") (8 . "LOUVERS") (62 . 7) (370 . 13) (100 . "AcDbLine") (10 4207.9411764706
3212.6696832579 0.0) (11 4241.7533936652 3212.6696832579 0.0))
((0 . "LINE") (100 . "AcDbEntity") (8 . "LOUVERS") (62 . 7) (370 . 13) (100 . "AcDbLine") (10 4241.7533936652
3212.6696832579 0.0) (11 4263.0769230769 3212.6696832579 0.0))
((0 . "LINE") (100 . "AcDbEntity") (8 . "LOUVERS") (62 . 7) (370 . 13) (100 . "AcDbLine") (10 4263.0769230769
3212.6696832579 0.0) (11 4297.6583710407 3212.6696832579 0.0))
((0 . "LINE") (100 . "AcDbEntity") (8 . "LOUVERS") (62 . 7) (370 . 13) (100 . "AcDbLine") (10 4297.6583710407
3212.6696832579 0.0) (11 4325.8371040724 3212.6696832579 0.0))
((0 . "LINE") (100 . "AcDbEntity") (8 . "LOUVERS") (62 . 7) (370 . 13) (100 . "AcDbLine") (10 4325.8371040724
3212.6696832579 0.0) (11 4364.0384615385 3212.6696832579 0.0))
((0 . "LINE") (100 . "AcDbEntity") (8 . "LOUVERS") (62 . 7) (370 . 13) (100 . "AcDbLine") (10 4364.0384615385
3212.6696832579 0.0) (11 4399.6153846154 3212.6696832579 0.0))
((0 . "LINE") (100 . "AcDbEntity") (8 . "LOUVERS") (62 . 7) (370 . 13) (100 . "AcDbLine") (10 4399.6153846154
3212.6696832579 0.0) (11 4434.9095022624 3212.6696832579 0.0))
((0 . "LINE") (100 . "AcDbEntity") (8 . "LOUVERS") (62 . 7) (370 . 13) (100 . "AcDbLine") (10 4434.9095022624
3212.6696832579 0.0) (11 4469.8642533937 3212.6696832579 0.0))
((0 . "LINE") (100 . "AcDbEntity") (8 . "LOUVERS") (62 . 7) (370 . 13) (100 . "AcDbLine") (10 4469.8642533937
3212.6696832579 0.0) (11 4505.2714932127 3212.6696832579 0.0))
((0 . "LINE") (100 . "AcDbEntity") (8 . "LOUVERS") (62 . 7) (370 . 13) (100 . "AcDbLine") (10 4505.2714932127
3212.6696832579 0.0) (11 4537.6923076923 3212.6696832579 0.0))
((0 . "LINE") (100 . "AcDbEntity") (8 . "LOUVERS") (62 . 7) (370 . 13) (100 . "AcDbLine") (10 4537.6923076923
3212.6696832579 0.0) (11 4573.4049773756 3212.6696832579 0.0))
((0 . "LINE") (100 . "AcDbEntity") (8 . "LOUVERS") (62 . 7) (370 . 13) (100 . "AcDbLine") (10 4573.4049773756
3212.6696832579 0.0) (11 4604.9095022624 3212.6696832579 0.0))
((0 . "LINE") (100 . "AcDbEntity") (8 . "LOUVERS") (62 . 7) (370 . 13) (100 . "AcDbLine") (10 4604.9095022624
3212.6696832579 0.0) (11 4647.3868778281 3212.6696832579 0.0))
((0 . "LINE") (100 . "AcDbEntity") (8 . "LOUVERS") (62 . 7) (370 . 13) (100 . "AcDbLine") (10 4647.3868778281
3212.6696832579 0.0) (11 4683.665158371 3212.6696832579 0.0))
((0 . "LINE") (100 . "AcDbEntity") (8 . "LOUVERS") (62 . 7) (370 . 13) (100 . "AcDbLine") (10 4683.665158371
3212.6696832579 0.0) (11 4731.2669683258 3212.6696832579 0.0))
((0 . "LINE") (100 . "AcDbEntity") (8 . "LOUVERS") (62 . 7) (370 . 13) (100 . "AcDbLine") (10 4731.2669683258
3212.6696832579 0.0) (11 4749.6040723982 3212.6696832579 0.0))
((0 . "LINE") (100 . "AcDbEntity") (8 . "LOUVERS") (62 . 7) (370 . 13) (100 . "AcDbLine") (10 4749.6040723982
3212.6696832579 0.0) (11 4796.7307692308 3212.6696832579 0.0))
((0 . "LINE") (100 . "AcDbEntity") (8 . "LOUVERS") (62 . 7) (370 . 13) (100 . "AcDbLine") (10 4796.7307692308
3212.6696832579 0.0) (11 4834.0497737557 3212.6696832579 0.0))
((0 . "LINE") (100 . "AcDbEntity") (8 . "LOUVERS") (62 . 7) (370 . 13) (100 . "AcDbLine") (10 4834.0497737557
3212.6696832579 0.0) (11 4861.5271493213 3212.6696832579 0.0))
((0 . "LINE") (100 . "AcDbEntity") (8 . "LOUVERS") (62 . 7) (370 . 13) (100 . "AcDbLine") (10 4861.5271493213
3212.6696832579 0.0) (11 4920.0339366516 3212.6696832579 0.0))
((0 . "LINE") (100 . "AcDbEntity") (8 . "LOUVERS") (62 . 7) (370 . 13) (100 . "AcDbLine") (10 4920.0339366516
3212.6696832579 0.0) (11 4968.1334841629 3212.6696832579 0.0))
((0 . "LINE") (100 . "AcDbEntity") (8 . "LOUVERS") (62 . 7) (370 . 13) (100 . "AcDbLine") (10 4968.1334841629
3212.6696832579 0.0) (11 5002.907239819 3212.6696832579 0.0))
((0 . "LINE") (100 . "AcDbEntity") (8 . "LOUVERS") (62 . 7) (370 . 13) (100 . "AcDbLine") (10 5002.907239819
3212.6696832579 0.0) (11 5042.7375565611 3212.6696832579 0.0))
((0 . "LINE") (100 . "AcDbEntity") (8 . "LOUVERS") (62 . 7) (370 . 13) (100 . "AcDbLine") (10 5042.7375565611
3212.6696832579 0.0) (11 5091.0180995475 3212.6696832579 0.0))
((0 . "LINE") (100 . "AcDbEntity") (8 . "LOUVERS") (62 . 7) (370 . 13) (100 . "AcDbLine") (10 5091.0180995475
3212.6696832579 0.0) (11 5124.7624434389 3212.6696832579 0.0))
((0 . "LINE") (100 . "AcDbEntity") (8 . "LOUVERS") (62 . 7) (370 . 13) (100 . "AcDbLine") (10 5124.7624434389
3212.6696832579 0.0) (11 5162.8619909502 3212.6696832579 0.0))
((0 . "LINE") (100 . "AcDbEntity") (8 . "LOUVERS") (62 . 7) (370 . 13) (100 . "AcDbLine") (10 5162.8619909502
3212.6696832579 0.0) (11 5195.2714932127 3212.6696832579 0.0))
((0 . "LINE") (100 . "AcDbEntity") (8 . "LOUVERS") (62 . 7) (370 . 13) (100 . "AcDbLine") (10 5195.2714932127
3212.6696832579 0.0) (11 5229.9095022624 3212.6696832579 0.0))
((0 . "LINE") (100 . "AcDbEntity") (8 . "LOUVERS") (62 . 7) (370 . 13) (100 . "AcDbLine") (10 5229.9095022624
3212.6696832579 0.0) (11 5262.6583710407 3212.6696832579 0.0))
((0 . "LINE") (100 . "AcDbEntity") (8 . "LOUVERS") (62 . 7) (370 . 13) (100 . "AcDbLine") (10 5262.6583710407
3212.6696832579 0.0) (11 5312.8846153846 3212.6696832579 0.0))
((0 . "LINE") (100 . "AcDbEntity") (8 . "LOUVERS") (62 . 7) (370 . 13) (100 . "AcDbLine") (10 5312.8846153846
3212.6696832579 0.0) (11 5341.3122171946 3212.6696832579 0.0))
((0 . "LINE") (100 . "AcDbEntity") (8 . "LOUVERS") (62 . 7) (370 . 13) (100 . "AcDbLine") (10 5341.3122171946
3212.6696832579 0.0) (11 5388.3484162896 3212.6696832579 0.0))
((0 . "LINE") (100 . "AcDbEntity") (8 . "LOUVERS") (62 . 7) (370 . 13) (100 . "AcDbLine") (10 5388.3484162896
3212.6696832579 0.0) (11 5454.242081448 3212.6696832579 0.0))
((0 . "LINE") (100 . "AcDbEntity") (8 . "LOUVERS") (62 . 7) (370 . 13) (100 . "AcDbLine") (10 5454.242081448
3212.6696832579 0.0) (11 5507.9751131222 3212.6696832579 0.0))
((0 . "LINE") (100 . "AcDbEntity") (8 . "LOUVERS") (62 . 7) (370 . 13) (100 . "AcDbLine") (10 5507.9751131222
3212.6696832579 0.0) (11 5531.1199095023 3212.6696832579 0.0))
((0 . "LINE") (100 . "AcDbEntity") (8 . "LOUVERS") (62 . 7) (370 . 13) (100 . "AcDbLine") (10 5531.1199095023
3212.6696832579 0.0) (11 5574.2194570136 3212.6696832579 0.0))
((0 . "LINE") (100 . "AcDbEntity") (8 . "LOUVERS") (62 . 7) (370 . 13) (100 . "AcDbLine") (10 5574.2194570136
3212.6696832579 0.0) (11 5600.3733031674 3212.6696832579 0.0))
((0 . "LINE") (100 . "AcDbEntity") (8 . "LOUVERS") (62 . 7) (370 . 13) (100 . "AcDbLine") (10 5600.3733031674
3212.6696832579 0.0) (11 5640.3167420814 3212.6696832579 0.0))
((0 . "LINE") (100 . "AcDbEntity") (8 . "LOUVERS") (62 . 7) (370 . 13) (100 . "AcDbLine") (10 5640.3167420814
3212.6696832579 0.0) (11 5675.1131221719 3212.6696832579 0.0))
((0 . "LINE") (100 . "AcDbEntity") (8 . "LOUVERS") (62 . 7) (370 . 13) (100 . "AcDbLine") (10 5675.1131221719
3212.6696832579 0.0) (11 5713.7895927602 3212.6696832579 0.0))
((0 . "LINE") (100 . "AcDbEntity") (8 . "LOUVERS") (62 . 7) (370 . 13) (100 . "AcDbLine") (10 5713.7895927602
3212.6696832579 0.0) (11 5747.2511312217 3212.6696832579 0.0))
((0 . "LINE") (100 . "AcDbEntity") (8 . "LOUVERS") (62 . 7) (370 . 13) (100 . "AcDbLine") (10 5747.2511312217
3212.6696832579 0.0) (11 5780.520361991 3212.6696832579 0.0))
((0 . "LINE") (100 . "AcDbEntity") (8 . "LOUVERS") (62 . 7) (370 . 13) (100 . "AcDbLine") (10 5780.520361991
3212.6696832579 0.0) (11 5816.5610859729 3212.6696832579 0.0))
((0 . "LINE") (100 . "AcDbEntity") (8 . "LOUVERS") (62 . 7) (370 . 13) (100 . "AcDbLine") (10 5816.5610859729
3212.6696832579 0.0) (11 5871.8438914027 3212.6696832579 0.0))
((0 . "LINE") (100 . "AcDbEntity") (8 . "LOUVERS") (62 . 7) (370 . 13) (100 . "AcDbLine") (10 5871.8438914027
3212.6696832579 0.0) (11 5896.4027149321 3212.6696832579 0.0))
((0 . "LINE") (100 . "AcDbEntity") (8 . "LOUVERS") (62 . 7) (370 . 13) (100 . "AcDbLine") (10 5896.4027149321
3212.6696832579 0.0) (11 5935.6561085973 3212.6696832579 0.0))
((0 . "LINE") (100 . "AcDbEntity") (8 . "LOUVERS") (62 . 7) (370 . 13) (100 . "AcDbLine") (10 5935.6561085973
3212.6696832579 0.0) (11 5965.0113122172 3212.6696832579 0.0))
((0 . "LINE") (100 . "AcDbEntity") (8 . "LOUVERS") (62 . 7) (370 . 13) (100 . "AcDbLine") (10 5965.0113122172
3212.6696832579 0.0) (11 6002.4660633484 3212.6696832579 0.0))
((0 . "LINE") (100 . "AcDbEntity") (8 . "LOUVERS") (62 . 7) (370 . 13) (100 . "AcDbLine") (10 6002.4660633484
3212.6696832579 0.0) (11 6036.0180995475 3212.6696832579 0.0))
((0 . "LINE") (100 . "AcDbEntity") (8 . "LOUVERS") (62 . 7) (370 . 13) (100 . "AcDbLine") (10 6036.0180995475
3212.6696832579 0.0) (11 6075.3393665158 3212.6696832579 0.0))
((0 . "LINE") (100 . "AcDbEntity") (8 . "LOUVERS") (62 . 7) (370 . 13) (100 . "AcDbLine") (10 6075.3393665158
3212.6696832579 0.0) (11 6116.2895927602 3212.6696832579 0.0))
((0 . "LINE") (100 . "AcDbEntity") (8 . "LOUVERS") (62 . 7) (370 . 13) (100 . "AcDbLine") (10 6116.2895927602
3212.6696832579 0.0) (11 6147.0701357466 3212.6696832579 0.0))
((0 . "LINE") (100 . "AcDbEntity") (8 . "LOUVERS") (62 . 7) (370 . 13) (100 . "AcDbLine") (10 6147.0701357466
3212.6696832579 0.0) (11 6180.2262443439 3212.6696832579 0.0))
((0 . "LINE") (100 . "AcDbEntity") (8 . "LOUVERS") (62 . 7) (370 . 13) (100 . "AcDbLine") (10 6180.2262443439
3212.6696832579 0.0) (11 6212.6583710407 3212.6696832579 0.0))
((0 . "LINE") (100 . "AcDbEntity") (8 . "LOUVERS") (62 . 7) (370 . 13) (100 . "AcDbLine") (10 6212.6583710407
3212.6696832579 0.0) (11 6246.8212669683 3212.6696832579 0.0))
((0 . "LINE") (100 . "AcDbEntity") (8 . "LOUVERS") (62 . 7) (370 . 13) (100 . "AcDbLine") (10 6246.8212669683
3212.6696832579 0.0) (11 6284.6266968326 3212.6696832579 0.0))
((0 . "LINE") (100 . "AcDbEntity") (8 . "LOUVERS") (62 . 7) (370 . 13) (100 . "AcDbLine") (10 6284.6266968326
3212.6696832579 0.0) (11 6319.8190045249 3212.6696832579 0.0))
((0 . "LINE") (100 . "AcDbEntity") (8 . "LOUVERS") (62 . 7) (370 . 13) (100 . "AcDbLine") (10 6319.8190045249
3212.6696832579 0.0) (11 6348.4049773756 3212.6696832579 0.0))
((0 . "LINE") (100 . "AcDbEntity") (8 . "LOUVERS") (62 . 7) (370 . 13) (100 . "AcDbLine") (10 6348.4049773756
3212.6696832579 0.0) (11 6395.0339366516 3212.6696832579 0.0))
((0 . "LINE") (100 . "AcDbEntity") (8 . "LOUVERS") (62 . 7) (370 . 13) (100 . "AcDbLine") (10 6395.0339366516
3212.6696832579 0.0) (11 6467.8733031674 3212.6696832579 0.0))
((0 . "LINE") (100 . "AcDbEntity") (8 . "LOUVERS") (62 . 7) (370 . 13) (100 . "AcDbLine") (10 6467.8733031674
3212.6696832579 0.0) (11 6489.7285067873 3212.6696832579 0.0))
((0 . "LINE") (100 . "AcDbEntity") (8 . "LOUVERS") (62 . 7) (370 . 13) (100 . "AcDbLine") (10 6489.7285067873
3212.6696832579 0.0) (11 6538.4615384615 3212.6696832579 0.0))
((0 . "LINE") (100 . "AcDbEntity") (8 . "LOUVERS") (62 . 7) (370 . 13) (100 . "AcDbLine") (10 6538.4615384615
3212.6696832579 0.0) (11 6559.0158371041 3212.6696832579 0.0))
((0 . "LINE") (100 . "AcDbEntity") (8 . "LOUVERS") (62 . 7) (370 . 13) (100 . "AcDbLine") (10 6559.0158371041
3212.6696832579 0.0) (11 6604.2194570136 3212.6696832579 0.0))
((0 . "LINE") (100 . "AcDbEntity") (8 . "LOUVERS") (62 . 7) (370 . 13) (100 . "AcDbLine") (10 6604.2194570136
3212.6696832579 0.0) (11 6627.9411764706 3212.6696832579 0.0))
((0 . "LINE") (100 . "AcDbEntity") (8 . "LOUVERS") (62 . 7) (370 . 13) (100 . "AcDbLine") (10 6627.9411764706
3212.6696832579 0.0) (11 6678.2239819005 3212.6696832579 0.0))
((0 . "LINE") (100 . "AcDbEntity") (8 . "LOUVERS") (62 . 7) (370 . 13) (100 . "AcDbLine") (10 6678.2239819005
3212.6696832579 0.0) (11 6709.8303167421 3212.6696832579 0.0))
((0 . "LINE") (100 . "AcDbEntity") (8 . "LOUVERS") (62 . 7) (370 . 13) (100 . "AcDbLine") (10 6709.8303167421
3212.6696832579 0.0) (11 6764.7058823529 3212.6696832579 0.0))
((0 . "LINE") (100 . "AcDbEntity") (8 . "LOUVERS") (62 . 7) (370 . 13) (100 . "AcDbLine") (10 6764.7058823529
3212.6696832579 0.0) (11 6764.7058823529 2952.4886877828 0.0))
((0 . "LINE") (100 . "AcDbEntity") (8 . "LOUVERS") (62 . 7) (370 . 13) (100 . "AcDbLine") (10 6764.7058823529
2952.4886877828 0.0) (11 6709.8303167421 2952.4886877828 0.0))
((0 . "LINE") (100 . "AcDbEntity") (8 . "LOUVERS") (62 . 7) (370 . 13) (100 . "AcDbLine") (10 6709.8303167421
2952.4886877828 0.0) (11 6678.2239819005 2952.4886877828 0.0))
((0 . "LINE") (100 . "AcDbEntity") (8 . "LOUVERS") (62 . 7) (370 . 13) (100 . "AcDbLine") (10 6678.2239819005
2952.4886877828 0.0) (11 6627.9411764706 2952.4886877828 0.0))
((0 . "LINE") (100 . "AcDbEntity") (8 . "LOUVERS") (62 . 7) (370 . 13) (100 . "AcDbLine") (10 6627.9411764706
2952.4886877828 0.0) (11 6604.2194570136 2952.4886877828 0.0))
((0 . "LINE") (100 . "AcDbEntity") (8 . "LOUVERS") (62 . 7) (370 . 13) (100 . "AcDbLine") (10 6604.2194570136
2952.4886877828 0.0) (11 6559.0158371041 2952.4886877828 0.0))
((0 . "LINE") (100 . "AcDbEntity") (8 . "LOUVERS") (62 . 7) (370 . 13) (100 . "AcDbLine") (10 6559.0158371041
2952.4886877828 0.0) (11 6538.4615384615 2952.4886877828 0.0))
((0 . "LINE") (100 . "AcDbEntity") (8 . "LOUVERS") (62 . 7) (370 . 13) (100 . "AcDbLine") (10 6538.4615384615
2952.4886877828 0.0) (11 6489.7285067873 2952.4886877828 0.0))
((0 . "LINE") (100 . "AcDbEntity") (8 . "LOUVERS") (62 . 7) (370 . 13) (100 . "AcDbLine") (10 6489.7285067873
2952.4886877828 0.0) (11 6467.8733031674 2952.4886877828 0.0))
((0 . "LINE") (100 . "AcDbEntity") (8 . "LOUVERS") (62 . 7) (370 . 13) (100 . "AcDbLine") (10 6467.8733031674
2952.4886877828 0.0) (11 6395.0339366516 2952.4886877828 0.0))
((0 . "LINE") (100 . "AcDbEntity") (8 . "LOUVERS") (62 . 7) (370 . 13) (100 . "AcDbLine") (10 6395.0339366516
2952.4886877828 0.0) (11 6348.4049773756 2952.4886877828 0.0))
((0 . "LINE") (100 . "AcDbEntity") (8 . "LOUVERS") (62 . 7) (370 . 13) (100 . "AcDbLine") (10 6348.4049773756
2952.4886877828 0.0) (11 6319.8190045249 2952.4886877828 0.0))
((0 . "LINE") (100 . "AcDbEntity") (8 . "LOUVERS") (62 . 7) (370 . 13) (100 . "AcDbLine") (10 6319.8190045249
2952.4886877828 0.0) (11 6284.6266968326 2952.4886877828 0.0))
((0 . "LINE") (100 . "AcDbEntity") (8 . "LOUVERS") (62 . 7) (370 . 13) (100 . "AcDbLine") (10 6284.6266968326
2952.4886877828 0.0) (11 6246.8212669683 2952.4886877828 0.0))
((0 . "LINE") (100 . "AcDbEntity") (8 . "LOUVERS") (62 . 7) (370 . 13) (100 . "AcDbLine") (10 6246.8212669683
2952.4886877828 0.0) (11 6212.6583710407 2952.4886877828 0.0))
((0 . "LINE") (100 . "AcDbEntity") (8 . "LOUVERS") (62 . 7) (370 . 13) (100 . "AcDbLine") (10 6212.6583710407
2952.4886877828 0.0) (11 6180.2262443439 2952.4886877828 0.0))
((0 . "LINE") (100 . "AcDbEntity") (8 . "LOUVERS") (62 . 7) (370 . 13) (100 . "AcDbLine") (10 6180.2262443439
2952.4886877828 0.0) (11 6147.0701357466 2952.4886877828 0.0))
((0 . "LINE") (100 . "AcDbEntity") (8 . "LOUVERS") (62 . 7) (370 . 13) (100 . "AcDbLine") (10 6147.0701357466
2952.4886877828 0.0) (11 6116.2895927602 2952.4886877828 0.0))
((0 . "LINE") (100 . "AcDbEntity") (8 . "LOUVERS") (62 . 7) (370 . 13) (100 . "AcDbLine") (10 6116.2895927602
2952.4886877828 0.0) (11 6075.3393665158 2952.4886877828 0.0))
((0 . "LINE") (100 . "AcDbEntity") (8 . "LOUVERS") (62 . 7) (370 . 13) (100 . "AcDbLine") (10 6075.3393665158
2952.4886877828 0.0) (11 6036.0180995475 2952.4886877828 0.0))
((0 . "LINE") (100 . "AcDbEntity") (8 . "LOUVERS") (62 . 7) (370 . 13) (100 . "AcDbLine") (10 6036.0180995475
2952.4886877828 0.0) (11 6002.4660633484 2952.4886877828 0.0))
((0 . "LINE") (100 . "AcDbEntity") (8 . "LOUVERS") (62 . 7) (370 . 13) (100 . "AcDbLine") (10 6002.4660633484
2952.4886877828 0.0) (11 5965.0113122172 2952.4886877828 0.0))
((0 . "LINE") (100 . "AcDbEntity") (8 . "LOUVERS") (62 . 7) (370 . 13) (100 . "AcDbLine") (10 5965.0113122172
2952.4886877828 0.0) (11 5935.6561085973 2952.4886877828 0.0))
((0 . "LINE") (100 . "AcDbEntity") (8 . "LOUVERS") (62 . 7) (370 . 13) (100 . "AcDbLine") (10 5935.6561085973
2952.4886877828 0.0) (11 5896.4027149321 2952.4886877828 0.0))
((0 . "LINE") (100 . "AcDbEntity") (8 . "LOUVERS") (62 . 7) (370 . 13) (100 . "AcDbLine") (10 5896.4027149321
2952.4886877828 0.0) (11 5871.8438914027 2952.4886877828 0.0))
((0 . "LINE") (100 . "AcDbEntity") (8 . "LOUVERS") (62 . 7) (370 . 13) (100 . "AcDbLine") (10 5871.8438914027
2952.4886877828 0.0) (11 5816.5610859729 2952.4886877828 0.0))
((0 . "LINE") (100 . "AcDbEntity") (8 . "LOUVERS") (62 . 7) (370 . 13) (100 . "AcDbLine") (10 5816.5610859729
2952.4886877828 0.0) (11 5780.520361991 2952.4886877828 0.0))
((0 . "LINE") (100 . "AcDbEntity") (8 . "LOUVERS") (62 . 7) (370 . 13) (100 . "AcDbLine") (10 5780.520361991
2952.4886877828 0.0) (11 5747.2511312217 2952.4886877828 0.0))
((0 . "LINE") (100 . "AcDbEntity") (8 . "LOUVERS") (62 . 7) (370 . 13) (100 . "AcDbLine") (10 5747.2511312217
2952.4886877828 0.0) (11 5713.7895927602 2952.4886877828 0.0))
((0 . "LINE") (100 . "AcDbEntity") (8 . "LOUVERS") (62 . 7) (370 . 13) (100 . "AcDbLine") (10 5713.7895927602
2952.4886877828 0.0) (11 5675.1131221719 2952.4886877828 0.0))
((0 . "LINE") (100 . "AcDbEntity") (8 . "LOUVERS") (62 . 7) (370 . 13) (100 . "AcDbLine") (10 5675.1131221719
2952.4886877828 0.0) (11 5640.3167420814 2952.4886877828 0.0))
((0 . "LINE") (100 . "AcDbEntity") (8 . "LOUVERS") (62 . 7) (370 . 13) (100 . "AcDbLine") (10 5640.3167420814
2952.4886877828 0.0) (11 5600.3733031674 2952.4886877828 0.0))
((0 . "LINE") (100 . "AcDbEntity") (8 . "LOUVERS") (62 . 7) (370 . 13) (100 . "AcDbLine") (10 5600.3733031674
2952.4886877828 0.0) (11 5574.2194570136 2952.4886877828 0.0))
((0 . "LINE") (100 . "AcDbEntity") (8 . "LOUVERS") (62 . 7) (370 . 13) (100 . "AcDbLine") (10 5574.2194570136
2952.4886877828 0.0) (11 5531.1199095023 2952.4886877828 0.0))
((0 . "LINE") (100 . "AcDbEntity") (8 . "LOUVERS") (62 . 7) (370 . 13) (100 . "AcDbLine") (10 5531.1199095023
2952.4886877828 0.0) (11 5507.9751131222 2952.4886877828 0.0))
((0 . "LINE") (100 . "AcDbEntity") (8 . "LOUVERS") (62 . 7) (370 . 13) (100 . "AcDbLine") (10 5507.9751131222
2952.4886877828 0.0) (11 5454.242081448 2952.4886877828 0.0))
((0 . "LINE") (100 . "AcDbEntity") (8 . "LOUVERS") (62 . 7) (370 . 13) (100 . "AcDbLine") (10 5454.242081448
2952.4886877828 0.0) (11 5388.3484162896 2952.4886877828 0.0))
((0 . "LINE") (100 . "AcDbEntity") (8 . "LOUVERS") (62 . 7) (370 . 13) (100 . "AcDbLine") (10 5388.3484162896
2952.4886877828 0.0) (11 5341.3122171946 2952.4886877828 0.0))
((0 . "LINE") (100 . "AcDbEntity") (8 . "LOUVERS") (62 . 7) (370 . 13) (100 . "AcDbLine") (10 5341.3122171946
2952.4886877828 0.0) (11 5312.8846153846 2952.4886877828 0.0))
((0 . "LINE") (100 . "AcDbEntity") (8 . "LOUVERS") (62 . 7) (370 . 13) (100 . "AcDbLine") (10 5312.8846153846
2952.4886877828 0.0) (11 5262.6583710407 2952.4886877828 0.0))
((0 . "LINE") (100 . "AcDbEntity") (8 . "LOUVERS") (62 . 7) (370 . 13) (100 . "AcDbLine") (10 5262.6583710407
2952.4886877828 0.0) (11 5229.9095022624 2952.4886877828 0.0))
((0 . "LINE") (100 . "AcDbEntity") (8 . "LOUVERS") (62 . 7) (370 . 13) (100 . "AcDbLine") (10 5229.9095022624
2952.4886877828 0.0) (11 5195.2714932127 2952.4886877828 0.0))
((0 . "LINE") (100 . "AcDbEntity") (8 . "LOUVERS") (62 . 7) (370 . 13) (100 . "AcDbLine") (10 5195.2714932127
2952.4886877828 0.0) (11 5162.8619909502 2952.4886877828 0.0))
((0 . "LINE") (100 . "AcDbEntity") (8 . "LOUVERS") (62 . 7) (370 . 13) (100 . "AcDbLine") (10 5162.8619909502
2952.4886877828 0.0) (11 5124.7624434389 2952.4886877828 0.0))
((0 . "LINE") (100 . "AcDbEntity") (8 . "LOUVERS") (62 . 7) (370 . 13) (100 . "AcDbLine") (10 5124.7624434389
2952.4886877828 0.0) (11 5091.0180995475 2952.4886877828 0.0))
((0 . "LINE") (100 . "AcDbEntity") (8 . "LOUVERS") (62 . 7) (370 . 13) (100 . "AcDbLine") (10 5091.0180995475
2952.4886877828 0.0) (11 5042.7375565611 2952.4886877828 0.0))
((0 . "LINE") (100 . "AcDbEntity") (8 . "LOUVERS") (62 . 7) (370 . 13) (100 . "AcDbLine") (10 5042.7375565611
2952.4886877828 0.0) (11 5002.907239819 2952.4886877828 0.0))
((0 . "LINE") (100 . "AcDbEntity") (8 . "LOUVERS") (62 . 7) (370 . 13) (100 . "AcDbLine") (10 5002.907239819
2952.4886877828 0.0) (11 4968.1334841629 2952.4886877828 0.0))
((0 . "LINE") (100 . "AcDbEntity") (8 . "LOUVERS") (62 . 7) (370 . 13) (100 . "AcDbLine") (10 4968.1334841629
2952.4886877828 0.0) (11 4920.0339366516 2952.4886877828 0.0))
((0 . "LINE") (100 . "AcDbEntity") (8 . "LOUVERS") (62 . 7) (370 . 13) (100 . "AcDbLine") (10 4920.0339366516
2952.4886877828 0.0) (11 4861.5271493213 2952.4886877828 0.0))
((0 . "LINE") (100 . "AcDbEntity") (8 . "LOUVERS") (62 . 7) (370 . 13) (100 . "AcDbLine") (10 4861.5271493213
2952.4886877828 0.0) (11 4834.0497737557 2952.4886877828 0.0))
((0 . "LINE") (100 . "AcDbEntity") (8 . "LOUVERS") (62 . 7) (370 . 13) (100 . "AcDbLine") (10 4834.0497737557
2952.4886877828 0.0) (11 4796.7307692308 2952.4886877828 0.0))
((0 . "LINE") (100 . "AcDbEntity") (8 . "LOUVERS") (62 . 7) (370 . 13) (100 . "AcDbLine") (10 4796.7307692308
2952.4886877828 0.0) (11 4749.6040723982 2952.4886877828 0.0))
((0 . "LINE") (100 . "AcDbEntity") (8 . "LOUVERS") (62 . 7) (370 . 13) (100 . "AcDbLine") (10 4749.6040723982
2952.4886877828 0.0) (11 4731.2669683258 2952.4886877828 0.0))
((0 . "LINE") (100 . "AcDbEntity") (8 . "LOUVERS") (62 . 7) (370 . 13) (100 . "AcDbLine") (10 4731.2669683258
2952.4886877828 0.0) (11 4683.665158371 2952.4886877828 0.0))
((0 . "LINE") (100 . "AcDbEntity") (8 . "LOUVERS") (62 . 7) (370 . 13) (100 . "AcDbLine") (10 4683.665158371
2952.4886877828 0.0) (11 4647.3868778281 2952.4886877828 0.0))
((0 . "LINE") (100 . "AcDbEntity") (8 . "LOUVERS") (62 . 7) (370 . 13) (100 . "AcDbLine") (10 4647.3868778281
2952.4886877828 0.0) (11 4604.9095022624 2952.4886877828 0.0))
((0 . "LINE") (100 . "AcDbEntity") (8 . "LOUVERS") (62 . 7) (370 . 13) (100 . "AcDbLine") (10 4604.9095022624
2952.4886877828 0.0) (11 4573.4049773756 2952.4886877828 0.0))
((0 . "LINE") (100 . "AcDbEntity") (8 . "LOUVERS") (62 . 7) (370 . 13) (100 . "AcDbLine") (10 4573.4049773756
2952.4886877828 0.0) (11 4537.6923076923 2952.4886877828 0.0))
((0 . "LINE") (100 . "AcDbEntity") (8 . "LOUVERS") (62 . 7) (370 . 13) (100 . "AcDbLine") (10 4537.6923076923
2952.4886877828 0.0) (11 4505.2714932127 2952.4886877828 0.0))
((0 . "LINE") (100 . "AcDbEntity") (8 . "LOUVERS") (62 . 7) (370 . 13) (100 . "AcDbLine") (10 4505.2714932127
2952.4886877828 0.0) (11 4469.8642533937 2952.4886877828 0.0))
((0 . "LINE") (100 . "AcDbEntity") (8 . "LOUVERS") (62 . 7) (370 . 13) (100 . "AcDbLine") (10 4469.8642533937
2952.4886877828 0.0) (11 4434.9095022624 2952.4886877828 0.0))
((0 . "LINE") (100 . "AcDbEntity") (8 . "LOUVERS") (62 . 7) (370 . 13) (100 . "AcDbLine") (10 4434.9095022624
2952.4886877828 0.0) (11 4399.6153846154 2952.4886877828 0.0))
((0 . "LINE") (100 . "AcDbEntity") (8 . "LOUVERS") (62 . 7) (370 . 13) (100 . "AcDbLine") (10 4399.6153846154
2952.4886877828 0.0) (11 4364.0384615385 2952.4886877828 0.0))
((0 . "LINE") (100 . "AcDbEntity") (8 . "LOUVERS") (62 . 7) (370 . 13) (100 . "AcDbLine") (10 4364.0384615385
2952.4886877828 0.0) (11 4325.8371040724 2952.4886877828 0.0))
((0 . "LINE") (100 . "AcDbEntity") (8 . "LOUVERS") (62 . 7) (370 . 13) (100 . "AcDbLine") (10 4325.8371040724
2952.4886877828 0.0) (11 4297.6583710407 2952.4886877828 0.0))
((0 . "LINE") (100 . "AcDbEntity") (8 . "LOUVERS") (62 . 7) (370 . 13) (100 . "AcDbLine") (10 4297.6583710407
2952.4886877828 0.0) (11 4263.0769230769 2952.4886877828 0.0))
((0 . "LINE") (100 . "AcDbEntity") (8 . "LOUVERS") (62 . 7) (370 . 13) (100 . "AcDbLine") (10 4263.0769230769
2952.4886877828 0.0) (11 4241.7533936652 2952.4886877828 0.0))
((0 . "LINE") (100 . "AcDbEntity") (8 . "LOUVERS") (62 . 7) (370 . 13) (100 . "AcDbLine") (10 4241.7533936652
2952.4886877828 0.0) (11 4207.9411764706 2952.4886877828 0.0))
((0 . "LINE") (100 . "AcDbEntity") (8 . "LOUVERS") (62 . 7) (370 . 13) (100 . "AcDbLine") (10 4207.9411764706
2952.4886877828 0.0) (11 4174.5588235294 2952.4886877828 0.0))
((0 . "LINE") (100 . "AcDbEntity") (8 . "LOUVERS") (62 . 7) (370 . 13) (100 . "AcDbLine") (10 4174.5588235294
2952.4886877828 0.0) (11 4134.8981900452 2952.4886877828 0.0))
((0 . "LINE") (100 . "AcDbEntity") (8 . "LOUVERS") (62 . 7) (370 . 13) (100 . "AcDbLine") (10 4134.8981900452
2952.4886877828 0.0) (11 4105.2036199095 2952.4886877828 0.0))
((0 . "LINE") (100 . "AcDbEntity") (8 . "LOUVERS") (62 . 7) (370 . 13) (100 . "AcDbLine") (10 4105.2036199095
2952.4886877828 0.0) (11 4061.0859728507 2952.4886877828 0.0))
((0 . "LINE") (100 . "AcDbEntity") (8 . "LOUVERS") (62 . 7) (370 . 13) (100 . "AcDbLine") (10 4061.0859728507
2952.4886877828 0.0) (11 4061.0859728507 3212.6696832579 0.0))
((0 . "LINE") (100 . "AcDbEntity") (8 . "LOUVERS") (62 . 7) (370 . 13) (100 . "AcDbLine") (10 4105.2036199095
3212.6696832579 0.0) (11 4105.2036199095 2952.4886877828 0.0))
((0 . "LINE") (100 . "AcDbEntity") (8 . "LOUVERS") (62 . 7) (370 . 13) (100 . "AcDbLine") (10 4134.8981900452
3212.6696832579 0.0) (11 4134.8981900452 2952.4886877828 0.0))
((0 . "LINE") (100 . "AcDbEntity") (8 . "LOUVERS") (62 . 7) (370 . 13) (100 . "AcDbLine") (10 4174.5588235294
3212.6696832579 0.0) (11 4174.5588235294 2952.4886877828 0.0))
((0 . "LINE") (100 . "AcDbEntity") (8 . "LOUVERS") (62 . 7) (370 . 13) (100 . "AcDbLine") (10 4207.9411764706
3212.6696832579 0.0) (11 4207.9411764706 2952.4886877828 0.0))
((0 . "LINE") (100 . "AcDbEntity") (8 . "LOUVERS") (62 . 7) (370 . 13) (100 . "AcDbLine") (10 4241.7533936652
3212.6696832579 0.0) (11 4241.7533936652 2952.4886877828 0.0))
((0 . "LINE") (100 . "AcDbEntity") (8 . "LOUVERS") (62 . 7) (370 . 13) (100 . "AcDbLine") (10 4263.0769230769
3212.6696832579 0.0) (11 4263.0769230769 2952.4886877828 0.0))
((0 . "LINE") (100 . "AcDbEntity") (8 . "LOUVERS") (62 . 7) (370 . 13) (100 . "AcDbLine") (10 4297.6583710407
3212.6696832579 0.0) (11 4297.6583710407 2952.4886877828 0.0))
((0 . "LINE") (100 . "AcDbEntity") (8 . "LOUVERS") (62 . 7) (370 . 13) (100 . "AcDbLine") (10 4325.8371040724
3212.6696832579 0.0) (11 4325.8371040724 2952.4886877828 0.0))
((0 . "LINE") (100 . "AcDbEntity") (8 . "LOUVERS") (62 . 7) (370 . 13) (100 . "AcDbLine") (10 4364.0384615385
3212.6696832579 0.0) (11 4364.0384615385 2952.4886877828 0.0))
((0 . "LINE") (100 . "AcDbEntity") (8 . "LOUVERS") (62 . 7) (370 . 13) (100 . "AcDbLine") (10 4399.6153846154
3212.6696832579 0.0) (11 4399.6153846154 2952.4886877828 0.0))
((0 . "LINE") (100 . "AcDbEntity") (8 . "LOUVERS") (62 . 7) (370 . 13) (100 . "AcDbLine") (10 4434.9095022624
3212.6696832579 0.0) (11 4434.9095022624 2952.4886877828 0.0))
((0 . "LINE") (100 . "AcDbEntity") (8 . "LOUVERS") (62 . 7) (370 . 13) (100 . "AcDbLine") (10 4469.8642533937
3212.6696832579 0.0) (11 4469.8642533937 2952.4886877828 0.0))
((0 . "LINE") (100 . "AcDbEntity") (8 . "LOUVERS") (62 . 7) (370 . 13) (100 . "AcDbLine") (10 4505.2714932127
3212.6696832579 0.0) (11 4505.2714932127 2952.4886877828 0.0))
((0 . "LINE") (100 . "AcDbEntity") (8 . "LOUVERS") (62 . 7) (370 . 13) (100 . "AcDbLine") (10 4537.6923076923
3212.6696832579 0.0) (11 4537.6923076923 2952.4886877828 0.0))
((0 . "LINE") (100 . "AcDbEntity") (8 . "LOUVERS") (62 . 7) (370 . 13) (100 . "AcDbLine") (10 4573.4049773756
3212.6696832579 0.0) (11 4573.4049773756 2952.4886877828 0.0))
((0 . "LINE") (100 . "AcDbEntity") (8 . "LOUVERS") (62 . 7) (370 . 13) (100 . "AcDbLine") (10 4604.9095022624
3212.6696832579 0.0) (11 4604.9095022624 2952.4886877828 0.0))
((0 . "LINE") (100 . "AcDbEntity") (8 . "LOUVERS") (62 . 7) (370 . 13) (100 . "AcDbLine") (10 4647.3868778281
3212.6696832579 0.0) (11 4647.3868778281 2952.4886877828 0.0))
((0 . "LINE") (100 . "AcDbEntity") (8 . "LOUVERS") (62 . 7) (370 . 13) (100 . "AcDbLine") (10 4683.665158371
3212.6696832579 0.0) (11 4683.665158371 2952.4886877828 0.0))
((0 . "LINE") (100 . "AcDbEntity") (8 . "LOUVERS") (62 . 7) (370 . 13) (100 . "AcDbLine") (10 4731.2669683258
3212.6696832579 0.0) (11 4731.2669683258 2952.4886877828 0.0))
((0 . "LINE") (100 . "AcDbEntity") (8 . "LOUVERS") (62 . 7) (370 . 13) (100 . "AcDbLine") (10 4749.6040723982
3212.6696832579 0.0) (11 4749.6040723982 2952.4886877828 0.0))
((0 . "LINE") (100 . "AcDbEntity") (8 . "LOUVERS") (62 . 7) (370 . 13) (100 . "AcDbLine") (10 4796.7307692308
3212.6696832579 0.0) (11 4796.7307692308 2952.4886877828 0.0))
((0 . "LINE") (100 . "AcDbEntity") (8 . "LOUVERS") (62 . 7) (370 . 13) (100 . "AcDbLine") (10 4834.0497737557
3212.6696832579 0.0) (11 4834.0497737557 2952.4886877828 0.0))
((0 . "LINE") (100 . "AcDbEntity") (8 . "LOUVERS") (62 . 7) (370 . 13) (100 . "AcDbLine") (10 4861.5271493213
3212.6696832579 0.0) (11 4861.5271493213 2952.4886877828 0.0))
((0 . "LINE") (100 . "AcDbEntity") (8 . "LOUVERS") (62 . 7) (370 . 13) (100 . "AcDbLine") (10 4920.0339366516
3212.6696832579 0.0) (11 4920.0339366516 2952.4886877828 0.0))
((0 . "LINE") (100 . "AcDbEntity") (8 . "LOUVERS") (62 . 7) (370 . 13) (100 . "AcDbLine") (10 4968.1334841629
3212.6696832579 0.0) (11 4968.1334841629 2952.4886877828 0.0))
((0 . "LINE") (100 . "AcDbEntity") (8 . "LOUVERS") (62 . 7) (370 . 13) (100 . "AcDbLine") (10 5002.907239819
3212.6696832579 0.0) (11 5002.907239819 2952.4886877828 0.0))
((0 . "LINE") (100 . "AcDbEntity") (8 . "LOUVERS") (62 . 7) (370 . 13) (100 . "AcDbLine") (10 5042.7375565611
3212.6696832579 0.0) (11 5042.7375565611 2952.4886877828 0.0))
((0 . "LINE") (100 . "AcDbEntity") (8 . "LOUVERS") (62 . 7) (370 . 13) (100 . "AcDbLine") (10 5091.0180995475
3212.6696832579 0.0) (11 5091.0180995475 2952.4886877828 0.0))
((0 . "LINE") (100 . "AcDbEntity") (8 . "LOUVERS") (62 . 7) (370 . 13) (100 . "AcDbLine") (10 5124.7624434389
3212.6696832579 0.0) (11 5124.7624434389 2952.4886877828 0.0))
((0 . "LINE") (100 . "AcDbEntity") (8 . "LOUVERS") (62 . 7) (370 . 13) (100 . "AcDbLine") (10 5162.8619909502
3212.6696832579 0.0) (11 5162.8619909502 2952.4886877828 0.0))
((0 . "LINE") (100 . "AcDbEntity") (8 . "LOUVERS") (62 . 7) (370 . 13) (100 . "AcDbLine") (10 5195.2714932127
3212.6696832579 0.0) (11 5195.2714932127 2952.4886877828 0.0))
((0 . "LINE") (100 . "AcDbEntity") (8 . "LOUVERS") (62 . 7) (370 . 13) (100 . "AcDbLine") (10 5229.9095022624
3212.6696832579 0.0) (11 5229.9095022624 2952.4886877828 0.0))
((0 . "LINE") (100 . "AcDbEntity") (8 . "LOUVERS") (62 . 7) (370 . 13) (100 . "AcDbLine") (10 5262.6583710407
3212.6696832579 0.0) (11 5262.6583710407 2952.4886877828 0.0))
((0 . "LINE") (100 . "AcDbEntity") (8 . "LOUVERS") (62 . 7) (370 . 13) (100 . "AcDbLine") (10 5312.8846153846
3212.6696832579 0.0) (11 5312.8846153846 2952.4886877828 0.0))
((0 . "LINE") (100 . "AcDbEntity") (8 . "LOUVERS") (62 . 7) (370 . 13) (100 . "AcDbLine") (10 5341.3122171946
3212.6696832579 0.0) (11 5341.3122171946 2952.4886877828 0.0))
((0 . "LINE") (100 . "AcDbEntity") (8 . "LOUVERS") (62 . 7) (370 . 13) (100 . "AcDbLine") (10 5388.3484162896
3212.6696832579 0.0) (11 5388.3484162896 2952.4886877828 0.0))
((0 . "LINE") (100 . "AcDbEntity") (8 . "LOUVERS") (62 . 7) (370 . 13) (100 . "AcDbLine") (10 5454.242081448
3212.6696832579 0.0) (11 5454.242081448 2952.4886877828 0.0))
((0 . "LINE") (100 . "AcDbEntity") (8 . "LOUVERS") (62 . 7) (370 . 13) (100 . "AcDbLine") (10 5507.9751131222
3212.6696832579 0.0) (11 5507.9751131222 2952.4886877828 0.0))
((0 . "LINE") (100 . "AcDbEntity") (8 . "LOUVERS") (62 . 7) (370 . 13) (100 . "AcDbLine") (10 5531.1199095023
3212.6696832579 0.0) (11 5531.1199095023 2952.4886877828 0.0))
((0 . "LINE") (100 . "AcDbEntity") (8 . "LOUVERS") (62 . 7) (370 . 13) (100 . "AcDbLine") (10 5574.2194570136
3212.6696832579 0.0) (11 5574.2194570136 2952.4886877828 0.0))
((0 . "LINE") (100 . "AcDbEntity") (8 . "LOUVERS") (62 . 7) (370 . 13) (100 . "AcDbLine") (10 5600.3733031674
3212.6696832579 0.0) (11 5600.3733031674 2952.4886877828 0.0))
((0 . "LINE") (100 . "AcDbEntity") (8 . "LOUVERS") (62 . 7) (370 . 13) (100 . "AcDbLine") (10 5640.3167420814
3212.6696832579 0.0) (11 5640.3167420814 2952.4886877828 0.0))
((0 . "LINE") (100 . "AcDbEntity") (8 . "LOUVERS") (62 . 7) (370 . 13) (100 . "AcDbLine") (10 5675.1131221719
3212.6696832579 0.0) (11 5675.1131221719 2952.4886877828 0.0))
((0 . "LINE") (100 . "AcDbEntity") (8 . "LOUVERS") (62 . 7) (370 . 13) (100 . "AcDbLine") (10 5713.7895927602
3212.6696832579 0.0) (11 5713.7895927602 2952.4886877828 0.0))
((0 . "LINE") (100 . "AcDbEntity") (8 . "LOUVERS") (62 . 7) (370 . 13) (100 . "AcDbLine") (10 5747.2511312217
3212.6696832579 0.0) (11 5747.2511312217 2952.4886877828 0.0))
((0 . "LINE") (100 . "AcDbEntity") (8 . "LOUVERS") (62 . 7) (370 . 13) (100 . "AcDbLine") (10 5780.520361991
3212.6696832579 0.0) (11 5780.520361991 2952.4886877828 0.0))
((0 . "LINE") (100 . "AcDbEntity") (8 . "LOUVERS") (62 . 7) (370 . 13) (100 . "AcDbLine") (10 5816.5610859729
3212.6696832579 0.0) (11 5816.5610859729 2952.4886877828 0.0))
((0 . "LINE") (100 . "AcDbEntity") (8 . "LOUVERS") (62 . 7) (370 . 13) (100 . "AcDbLine") (10 5871.8438914027
3212.6696832579 0.0) (11 5871.8438914027 2952.4886877828 0.0))
((0 . "LINE") (100 . "AcDbEntity") (8 . "LOUVERS") (62 . 7) (370 . 13) (100 . "AcDbLine") (10 5896.4027149321
3212.6696832579 0.0) (11 5896.4027149321 2952.4886877828 0.0))
((0 . "LINE") (100 . "AcDbEntity") (8 . "LOUVERS") (62 . 7) (370 . 13) (100 . "AcDbLine") (10 5935.6561085973
3212.6696832579 0.0) (11 5935.6561085973 2952.4886877828 0.0))
((0 . "LINE") (100 . "AcDbEntity") (8 . "LOUVERS") (62 . 7) (370 . 13) (100 . "AcDbLine") (10 5965.0113122172
3212.6696832579 0.0) (11 5965.0113122172 2952.4886877828 0.0))
((0 . "LINE") (100 . "AcDbEntity") (8 . "LOUVERS") (62 . 7) (370 . 13) (100 . "AcDbLine") (10 6002.4660633484
3212.6696832579 0.0) (11 6002.4660633484 2952.4886877828 0.0))
((0 . "LINE") (100 . "AcDbEntity") (8 . "LOUVERS") (62 . 7) (370 . 13) (100 . "AcDbLine") (10 6036.0180995475
3212.6696832579 0.0) (11 6036.0180995475 2952.4886877828 0.0))
((0 . "LINE") (100 . "AcDbEntity") (8 . "LOUVERS") (62 . 7) (370 . 13) (100 . "AcDbLine") (10 6075.3393665158
3212.6696832579 0.0) (11 6075.3393665158 2952.4886877828 0.0))
((0 . "LINE") (100 . "AcDbEntity") (8 . "LOUVERS") (62 . 7) (370 . 13) (100 . "AcDbLine") (10 6116.2895927602
3212.6696832579 0.0) (11 6116.2895927602 2952.4886877828 0.0))
((0 . "LINE") (100 . "AcDbEntity") (8 . "LOUVERS") (62 . 7) (370 . 13) (100 . "AcDbLine") (10 6147.0701357466
3212.6696832579 0.0) (11 6147.0701357466 2952.4886877828 0.0))
((0 . "LINE") (100 . "AcDbEntity") (8 . "LOUVERS") (62 . 7) (370 . 13) (100 . "AcDbLine") (10 6180.2262443439
3212.6696832579 0.0) (11 6180.2262443439 2952.4886877828 0.0))
((0 . "LINE") (100 . "AcDbEntity") (8 . "LOUVERS") (62 . 7) (370 . 13) (100 . "AcDbLine") (10 6212.6583710407
3212.6696832579 0.0) (11 6212.6583710407 2952.4886877828 0.0))
((0 . "LINE") (100 . "AcDbEntity") (8 . "LOUVERS") (62 . 7) (370 . 13) (100 . "AcDbLine") (10 6246.8212669683
3212.6696832579 0.0) (11 6246.8212669683 2952.4886877828 0.0))
((0 . "LINE") (100 . "AcDbEntity") (8 . "LOUVERS") (62 . 7) (370 . 13) (100 . "AcDbLine") (10 6284.6266968326
3212.6696832579 0.0) (11 6284.6266968326 2952.4886877828 0.0))
((0 . "LINE") (100 . "AcDbEntity") (8 . "LOUVERS") (62 . 7) (370 . 13) (100 . "AcDbLine") (10 6319.8190045249
3212.6696832579 0.0) (11 6319.8190045249 2952.4886877828 0.0))
((0 . "LINE") (100 . "AcDbEntity") (8 . "LOUVERS") (62 . 7) (370 . 13) (100 . "AcDbLine") (10 6348.4049773756
3212.6696832579 0.0) (11 6348.4049773756 2952.4886877828 0.0))
((0 . "LINE") (100 . "AcDbEntity") (8 . "LOUVERS") (62 . 7) (370 . 13) (100 . "AcDbLine") (10 6395.0339366516
3212.6696832579 0.0) (11 6395.0339366516 2952.4886877828 0.0))
((0 . "LINE") (100 . "AcDbEntity") (8 . "LOUVERS") (62 . 7) (370 . 13) (100 . "AcDbLine") (10 6467.8733031674
3212.6696832579 0.0) (11 6467.8733031674 2952.4886877828 0.0))
((0 . "LINE") (100 . "AcDbEntity") (8 . "LOUVERS") (62 . 7) (370 . 13) (100 . "AcDbLine") (10 6489.7285067873
3212.6696832579 0.0) (11 6489.7285067873 2952.4886877828 0.0))
((0 . "LINE") (100 . "AcDbEntity") (8 . "LOUVERS") (62 . 7) (370 . 13) (100 . "AcDbLine") (10 6538.4615384615
3212.6696832579 0.0) (11 6538.4615384615 2952.4886877828 0.0))
((0 . "LINE") (100 . "AcDbEntity") (8 . "LOUVERS") (62 . 7) (370 . 13) (100 . "AcDbLine") (10 6559.0158371041
3212.6696832579 0.0) (11 6559.0158371041 2952.4886877828 0.0))
((0 . "LINE") (100 . "AcDbEntity") (8 . "LOUVERS") (62 . 7) (370 . 13) (100 . "AcDbLine") (10 6604.2194570136
3212.6696832579 0.0) (11 6604.2194570136 2952.4886877828 0.0))
((0 . "LINE") (100 . "AcDbEntity") (8 . "LOUVERS") (62 . 7) (370 . 13) (100 . "AcDbLine") (10 6627.9411764706
3212.6696832579 0.0) (11 6627.9411764706 2952.4886877828 0.0))
((0 . "LINE") (100 . "AcDbEntity") (8 . "LOUVERS") (62 . 7) (370 . 13) (100 . "AcDbLine") (10 6678.2239819005
3212.6696832579 0.0) (11 6678.2239819005 2952.4886877828 0.0))
((0 . "LINE") (100 . "AcDbEntity") (8 . "LOUVERS") (62 . 7) (370 . 13) (100 . "AcDbLine") (10 6709.8303167421
3212.6696832579 0.0) (11 6709.8303167421 2952.4886877828 0.0))
((0 . "LINE") (100 . "AcDbEntity") (8 . "LOUVERS") (62 . 7) (370 . 13) (100 . "AcDbLine") (10 4355.2036199095
2194.5701357466 0.0) (11 4405.5995475113 2194.5701357466 0.0))
((0 . "LINE") (100 . "AcDbEntity") (8 . "LOUVERS") (62 . 7) (370 . 13) (100 . "AcDbLine") (10 4405.5995475113
2194.5701357466 0.0) (11 4435.2488687783 2194.5701357466 0.0))
((0 . "LINE") (100 . "AcDbEntity") (8 . "LOUVERS") (62 . 7) (370 . 13) (100 . "AcDbLine") (10 4435.2488687783
2194.5701357466 0.0) (11 4479.1628959276 2194.5701357466 0.0))
((0 . "LINE") (100 . "AcDbEntity") (8 . "LOUVERS") (62 . 7) (370 . 13) (100 . "AcDbLine") (10 4479.1628959276
2194.5701357466 0.0) (11 4513.9479638009 2194.5701357466 0.0))
((0 . "LINE") (100 . "AcDbEntity") (8 . "LOUVERS") (62 . 7) (370 . 13) (100 . "AcDbLine") (10 4513.9479638009
2194.5701357466 0.0) (11 4546.6968325792 2194.5701357466 0.0))
((0 . "LINE") (100 . "AcDbEntity") (8 . "LOUVERS") (62 . 7) (370 . 13) (100 . "AcDbLine") (10 4546.6968325792
2194.5701357466 0.0) (11 4579.7850678733 2194.5701357466 0.0))
((0 . "LINE") (100 . "AcDbEntity") (8 . "LOUVERS") (62 . 7) (370 . 13) (100 . "AcDbLine") (10 4579.7850678733
2194.5701357466 0.0) (11 4604.8529411765 2194.5701357466 0.0))
((0 . "LINE") (100 . "AcDbEntity") (8 . "LOUVERS") (62 . 7) (370 . 13) (100 . "AcDbLine") (10 4604.8529411765
2194.5701357466 0.0) (11 4641.8438914027 2194.5701357466 0.0))
((0 . "LINE") (100 . "AcDbEntity") (8 . "LOUVERS") (62 . 7) (370 . 13) (100 . "AcDbLine") (10 4641.8438914027
2194.5701357466 0.0) (11 4660.6334841629 2194.5701357466 0.0))
((0 . "LINE") (100 . "AcDbEntity") (8 . "LOUVERS") (62 . 7) (370 . 13) (100 . "AcDbLine") (10 4660.6334841629
2194.5701357466 0.0) (11 4660.6334841629 2183.257918552 0.0))
((0 . "LINE") (100 . "AcDbEntity") (8 . "LOUVERS") (62 . 7) (370 . 13) (100 . "AcDbLine") (10 4660.6334841629
2183.257918552 0.0) (11 4660.6334841629 972.850678733 0.0))
((0 . "LINE") (100 . "AcDbEntity") (8 . "LOUVERS") (62 . 7) (370 . 13) (100 . "AcDbLine") (10 4660.6334841629
972.850678733 0.0) (11 4641.8438914027 972.850678733 0.0))
((0 . "LINE") (100 . "AcDbEntity") (8 . "LOUVERS") (62 . 7) (370 . 13) (100 . "AcDbLine") (10 4641.8438914027
972.850678733 0.0) (11 4604.8529411765 972.850678733 0.0))
((0 . "LINE") (100 . "AcDbEntity") (8 . "LOUVERS") (62 . 7) (370 . 13) (100 . "AcDbLine") (10 4604.8529411765
972.850678733 0.0) (11 4579.7850678733 972.850678733 0.0))
((0 . "LINE") (100 . "AcDbEntity") (8 . "LOUVERS") (62 . 7) (370 . 13) (100 . "AcDbLine") (10 4579.7850678733
972.850678733 0.0) (11 4546.6968325792 972.850678733 0.0))
((0 . "LINE") (100 . "AcDbEntity") (8 . "LOUVERS") (62 . 7) (370 . 13) (100 . "AcDbLine") (10 4546.6968325792
972.850678733 0.0) (11 4513.9479638009 972.850678733 0.0))
((0 . "LINE") (100 . "AcDbEntity") (8 . "LOUVERS") (62 . 7) (370 . 13) (100 . "AcDbLine") (10 4513.9479638009
972.850678733 0.0) (11 4479.1628959276 972.850678733 0.0))
((0 . "LINE") (100 . "AcDbEntity") (8 . "LOUVERS") (62 . 7) (370 . 13) (100 . "AcDbLine") (10 4479.1628959276
972.850678733 0.0) (11 4435.2488687783 972.850678733 0.0))
((0 . "LINE") (100 . "AcDbEntity") (8 . "LOUVERS") (62 . 7) (370 . 13) (100 . "AcDbLine") (10 4435.2488687783
972.850678733 0.0) (11 4405.5995475113 972.850678733 0.0))
((0 . "LINE") (100 . "AcDbEntity") (8 . "LOUVERS") (62 . 7) (370 . 13) (100 . "AcDbLine") (10 4405.5995475113
972.850678733 0.0) (11 4355.2036199095 972.850678733 0.0))
((0 . "LINE") (100 . "AcDbEntity") (8 . "LOUVERS") (62 . 7) (370 . 13) (100 . "AcDbLine") (10 4355.2036199095
972.850678733 0.0) (11 4355.2036199095 2194.5701357466 0.0))
((0 . "LINE") (100 . "AcDbEntity") (8 . "LOUVERS") (62 . 7) (370 . 13) (100 . "AcDbLine") (10 4405.5995475113
2194.5701357466 0.0) (11 4405.5995475113 972.850678733 0.0))
((0 . "LINE") (100 . "AcDbEntity") (8 . "LOUVERS") (62 . 7) (370 . 13) (100 . "AcDbLine") (10 4435.2488687783
2194.5701357466 0.0) (11 4435.2488687783 972.850678733 0.0))
((0 . "LINE") (100 . "AcDbEntity") (8 . "LOUVERS") (62 . 7) (370 . 13) (100 . "AcDbLine") (10 4479.1628959276
2194.5701357466 0.0) (11 4479.1628959276 972.850678733 0.0))
((0 . "LINE") (100 . "AcDbEntity") (8 . "LOUVERS") (62 . 7) (370 . 13) (100 . "AcDbLine") (10 4513.9479638009
2194.5701357466 0.0) (11 4513.9479638009 972.850678733 0.0))
((0 . "LINE") (100 . "AcDbEntity") (8 . "LOUVERS") (62 . 7) (370 . 13) (100 . "AcDbLine") (10 4546.6968325792
2194.5701357466 0.0) (11 4546.6968325792 972.850678733 0.0))
((0 . "LINE") (100 . "AcDbEntity") (8 . "LOUVERS") (62 . 7) (370 . 13) (100 . "AcDbLine") (10 4579.7850678733
2194.5701357466 0.0) (11 4579.7850678733 972.850678733 0.0))
((0 . "LINE") (100 . "AcDbEntity") (8 . "LOUVERS") (62 . 7) (370 . 13) (100 . "AcDbLine") (10 4604.8529411765
2194.5701357466 0.0) (11 4604.8529411765 972.850678733 0.0))
((0 . "LINE") (100 . "AcDbEntity") (8 . "LOUVERS") (62 . 7) (370 . 13) (100 . "AcDbLine") (10 4641.8438914027
2194.5701357466 0.0) (11 4641.8438914027 972.850678733 0.0))
((0 . "LINE") (100 . "AcDbEntity") (8 . "LOUVERS") (62 . 7) (370 . 13) (100 . "AcDbLine") (10 6210.407239819
2194.5701357466 0.0) (11 6244.6606334842 2194.5701357466 0.0))
((0 . "LINE") (100 . "AcDbEntity") (8 . "LOUVERS") (62 . 7) (370 . 13) (100 . "AcDbLine") (10 6244.6606334842
2194.5701357466 0.0) (11 6285.7013574661 2194.5701357466 0.0))
((0 . "LINE") (100 . "AcDbEntity") (8 . "LOUVERS") (62 . 7) (370 . 13) (100 . "AcDbLine") (10 6285.7013574661
2194.5701357466 0.0) (11 6311.1877828054 2194.5701357466 0.0))
((0 . "LINE") (100 . "AcDbEntity") (8 . "LOUVERS") (62 . 7) (370 . 13) (100 . "AcDbLine") (10 6311.1877828054
2194.5701357466 0.0) (11 6352.6470588235 2194.5701357466 0.0))
((0 . "LINE") (100 . "AcDbEntity") (8 . "LOUVERS") (62 . 7) (370 . 13) (100 . "AcDbLine") (10 6352.6470588235
2194.5701357466 0.0) (11 6379.3325791855 2194.5701357466 0.0))
((0 . "LINE") (100 . "AcDbEntity") (8 . "LOUVERS") (62 . 7) (370 . 13) (100 . "AcDbLine") (10 6379.3325791855
2194.5701357466 0.0) (11 6414.5135746606 2194.5701357466 0.0))
((0 . "LINE") (100 . "AcDbEntity") (8 . "LOUVERS") (62 . 7) (370 . 13) (100 . "AcDbLine") (10 6414.5135746606
2194.5701357466 0.0) (11 6445.5882352941 2194.5701357466 0.0))
((0 . "LINE") (100 . "AcDbEntity") (8 . "LOUVERS") (62 . 7) (370 . 13) (100 . "AcDbLine") (10 6445.5882352941
2194.5701357466 0.0) (11 6492.3416289593 2194.5701357466 0.0))
((0 . "LINE") (100 . "AcDbEntity") (8 . "LOUVERS") (62 . 7) (370 . 13) (100 . "AcDbLine") (10 6492.3416289593
2194.5701357466 0.0) (11 6538.4615384615 2194.5701357466 0.0))
((0 . "LINE") (100 . "AcDbEntity") (8 . "LOUVERS") (62 . 7) (370 . 13) (100 . "AcDbLine") (10 6538.4615384615
2194.5701357466 0.0) (11 6538.4615384615 972.850678733 0.0))
((0 . "LINE") (100 . "AcDbEntity") (8 . "LOUVERS") (62 . 7) (370 . 13) (100 . "AcDbLine") (10 6538.4615384615
972.850678733 0.0) (11 6492.3416289593 972.850678733 0.0))
((0 . "LINE") (100 . "AcDbEntity") (8 . "LOUVERS") (62 . 7) (370 . 13) (100 . "AcDbLine") (10 6492.3416289593
972.850678733 0.0) (11 6445.5882352941 972.850678733 0.0))
((0 . "LINE") (100 . "AcDbEntity") (8 . "LOUVERS") (62 . 7) (370 . 13) (100 . "AcDbLine") (10 6445.5882352941
972.850678733 0.0) (11 6414.5135746606 972.850678733 0.0))
((0 . "LINE") (100 . "AcDbEntity") (8 . "LOUVERS") (62 . 7) (370 . 13) (100 . "AcDbLine") (10 6414.5135746606
972.850678733 0.0) (11 6379.3325791855 972.850678733 0.0))
((0 . "LINE") (100 . "AcDbEntity") (8 . "LOUVERS") (62 . 7) (370 . 13) (100 . "AcDbLine") (10 6379.3325791855
972.850678733 0.0) (11 6352.6470588235 972.850678733 0.0))
((0 . "LINE") (100 . "AcDbEntity") (8 . "LOUVERS") (62 . 7) (370 . 13) (100 . "AcDbLine") (10 6352.6470588235
972.850678733 0.0) (11 6311.1877828054 972.850678733 0.0))
((0 . "LINE") (100 . "AcDbEntity") (8 . "LOUVERS") (62 . 7) (370 . 13) (100 . "AcDbLine") (10 6311.1877828054
972.850678733 0.0) (11 6285.7013574661 972.850678733 0.0))
((0 . "LINE") (100 . "AcDbEntity") (8 . "LOUVERS") (62 . 7) (370 . 13) (100 . "AcDbLine") (10 6285.7013574661
972.850678733 0.0) (11 6244.6606334842 972.850678733 0.0))
((0 . "LINE") (100 . "AcDbEntity") (8 . "LOUVERS") (62 . 7) (370 . 13) (100 . "AcDbLine") (10 6244.6606334842
972.850678733 0.0) (11 6210.407239819 972.850678733 0.0))
((0 . "LINE") (100 . "AcDbEntity") (8 . "LOUVERS") (62 . 7) (370 . 13) (100 . "AcDbLine") (10 6210.407239819
972.850678733 0.0) (11 6210.407239819 2183.257918552 0.0))
((0 . "LINE") (100 . "AcDbEntity") (8 . "LOUVERS") (62 . 7) (370 . 13) (100 . "AcDbLine") (10 6210.407239819
2183.257918552 0.0) (11 6210.407239819 2194.5701357466 0.0))
((0 . "LINE") (100 . "AcDbEntity") (8 . "LOUVERS") (62 . 7) (370 . 13) (100 . "AcDbLine") (10 6244.6606334842
2194.5701357466 0.0) (11 6244.6606334842 972.850678733 0.0))
((0 . "LINE") (100 . "AcDbEntity") (8 . "LOUVERS") (62 . 7) (370 . 13) (100 . "AcDbLine") (10 6285.7013574661
2194.5701357466 0.0) (11 6285.7013574661 972.850678733 0.0))
((0 . "LINE") (100 . "AcDbEntity") (8 . "LOUVERS") (62 . 7) (370 . 13) (100 . "AcDbLine") (10 6311.1877828054
2194.5701357466 0.0) (11 6311.1877828054 972.850678733 0.0))
((0 . "LINE") (100 . "AcDbEntity") (8 . "LOUVERS") (62 . 7) (370 . 13) (100 . "AcDbLine") (10 6352.6470588235
2194.5701357466 0.0) (11 6352.6470588235 972.850678733 0.0))
((0 . "LINE") (100 . "AcDbEntity") (8 . "LOUVERS") (62 . 7) (370 . 13) (100 . "AcDbLine") (10 6379.3325791855
2194.5701357466 0.0) (11 6379.3325791855 972.850678733 0.0))
((0 . "LINE") (100 . "AcDbEntity") (8 . "LOUVERS") (62 . 7) (370 . 13) (100 . "AcDbLine") (10 6414.5135746606
2194.5701357466 0.0) (11 6414.5135746606 972.850678733 0.0))
((0 . "LINE") (100 . "AcDbEntity") (8 . "LOUVERS") (62 . 7) (370 . 13) (100 . "AcDbLine") (10 6445.5882352941
2194.5701357466 0.0) (11 6445.5882352941 972.850678733 0.0))
((0 . "LINE") (100 . "AcDbEntity") (8 . "LOUVERS") (62 . 7) (370 . 13) (100 . "AcDbLine") (10 6492.3416289593
2194.5701357466 0.0) (11 6492.3416289593 972.850678733 0.0))
((0 . "LINE") (100 . "AcDbEntity") (8 . "LOUVERS") (62 . 7) (370 . 13) (100 . "AcDbLine") (10 13291.8552036199
5531.6742081448 0.0) (11 13325.7918552036 5531.6742081448 0.0))
((0 . "LINE") (100 . "AcDbEntity") (8 . "LOUVERS") (62 . 7) (370 . 13) (100 . "AcDbLine") (10 13823.5294117647
5531.6742081448 0.0) (11 13823.5294117647 5045.2488687783 0.0))
((0 . "LINE") (100 . "AcDbEntity") (8 . "WINDOWS") (62 . 7) (370 . 13) (100 . "AcDbLine") (10 13823.5294117647
5045.2488687783 0.0) (11 13823.5294117647 3800.9049773756 0.0))
((0 . "LINE") (100 . "AcDbEntity") (8 . "LOUVERS") (62 . 7) (370 . 13) (100 . "AcDbLine") (10 13823.5294117647
3800.9049773756 0.0) (11 13772.3755656109 3800.9049773756 0.0))
((0 . "LINE") (100 . "AcDbEntity") (8 . "LOUVERS") (62 . 7) (370 . 13) (100 . "AcDbLine") (10 13772.3755656109
3800.9049773756 0.0) (11 13707.8959276018 3800.9049773756 0.0))
((0 . "LINE") (100 . "AcDbEntity") (8 . "LOUVERS") (62 . 7) (370 . 13) (100 . "AcDbLine") (10 13707.8959276018
3800.9049773756 0.0) (11 13690.9389140272 3800.9049773756 0.0))
((0 . "LINE") (100 . "AcDbEntity") (8 . "LOUVERS") (62 . 7) (370 . 13) (100 . "AcDbLine") (10 13690.9389140272
3800.9049773756 0.0) (11 13625.4524886878 3800.9049773756 0.0))
((0 . "LINE") (100 . "AcDbEntity") (8 . "LOUVERS") (62 . 7) (370 . 13) (100 . "AcDbLine") (10 13625.4524886878
3800.9049773756 0.0) (11 13543.5520361991 3800.9049773756 0.0))
((0 . "LINE") (100 . "AcDbEntity") (8 . "LOUVERS") (62 . 7) (370 . 13) (100 . "AcDbLine") (10 13543.5520361991
3800.9049773756 0.0) (11 13480.4524886878 3800.9049773756 0.0))
((0 . "LINE") (100 . "AcDbEntity") (8 . "LOUVERS") (62 . 7) (370 . 13) (100 . "AcDbLine") (10 13480.4524886878
3800.9049773756 0.0) (11 13464.7850678733 3800.9049773756 0.0))
((0 . "LINE") (100 . "AcDbEntity") (8 . "LOUVERS") (62 . 7) (370 . 13) (100 . "AcDbLine") (10 13464.7850678733
3800.9049773756 0.0) (11 13386.9230769231 3800.9049773756 0.0))
((0 . "LINE") (100 . "AcDbEntity") (8 . "LOUVERS") (62 . 7) (370 . 13) (100 . "AcDbLine") (10 13386.9230769231
3800.9049773756 0.0) (11 13326.334841629 3800.9049773756 0.0))
((0 . "LINE") (100 . "AcDbEntity") (8 . "LOUVERS") (62 . 7) (370 . 13) (100 . "AcDbLine") (10 13326.334841629
3800.9049773756 0.0) (11 13291.8552036199 3800.9049773756 0.0))
((0 . "LINE") (100 . "AcDbEntity") (8 . "LOUVERS") (62 . 7) (370 . 13) (100 . "AcDbLine") (10 13291.8552036199
3800.9049773756 0.0) (11 13291.8552036199 5531.6742081448 0.0))
((0 . "LINE") (100 . "AcDbEntity") (8 . "LOUVERS") (62 . 7) (370 . 13) (100 . "AcDbLine") (10 13326.334841629
5531.6742081448 0.0) (11 13326.334841629 3800.9049773756 0.0))
((0 . "LINE") (100 . "AcDbEntity") (8 . "LOUVERS") (62 . 7) (370 . 13) (100 . "AcDbLine") (10 13386.9230769231
5531.6742081448 0.0) (11 13386.9230769231 3800.9049773756 0.0))
((0 . "LINE") (100 . "AcDbEntity") (8 . "LOUVERS") (62 . 7) (370 . 13) (100 . "AcDbLine") (10 13464.7850678733
5531.6742081448 0.0) (11 13464.7850678733 3800.9049773756 0.0))
((0 . "LINE") (100 . "AcDbEntity") (8 . "LOUVERS") (62 . 7) (370 . 13) (100 . "AcDbLine") (10 13480.4524886878
5531.6742081448 0.0) (11 13480.4524886878 3800.9049773756 0.0))
((0 . "LINE") (100 . "AcDbEntity") (8 . "LOUVERS") (62 . 7) (370 . 13) (100 . "AcDbLine") (10 13543.5520361991
5531.6742081448 0.0) (11 13543.5520361991 3800.9049773756 0.0))
((0 . "LINE") (100 . "AcDbEntity") (8 . "LOUVERS") (62 . 7) (370 . 13) (100 . "AcDbLine") (10 13625.4524886878
5531.6742081448 0.0) (11 13625.4524886878 3800.9049773756 0.0))
((0 . "LINE") (100 . "AcDbEntity") (8 . "LOUVERS") (62 . 7) (370 . 13) (100 . "AcDbLine") (10 13690.9389140272
5531.6742081448 0.0) (11 13690.9389140272 3800.9049773756 0.0))
((0 . "LINE") (100 . "AcDbEntity") (8 . "LOUVERS") (62 . 7) (370 . 13) (100 . "AcDbLine") (10 13707.8959276018
5531.6742081448 0.0) (11 13707.8959276018 3800.9049773756 0.0))
((0 . "LINE") (100 . "AcDbEntity") (8 . "LOUVERS") (62 . 7) (370 . 13) (100 . "AcDbLine") (10 13772.3755656109
5531.6742081448 0.0) (11 13772.3755656109 3800.9049773756 0.0))
((0 . "LINE") (100 . "AcDbEntity") (8 . "LOUVERS") (62 . 7) (370 . 13) (100 . "AcDbLine") (10 15825.7918552036
5531.6742081448 0.0) (11 15831.9570135747 5531.6742081448 0.0))
((0 . "LINE") (100 . "AcDbEntity") (8 . "LOUVERS") (62 . 7) (370 . 13) (100 . "AcDbLine") (10 15831.9570135747
5531.6742081448 0.0) (11 15859.7285067873 5531.6742081448 0.0))
((0 . "LINE") (100 . "AcDbEntity") (8 . "LOUVERS") (62 . 7) (370 . 13) (100 . "AcDbLine") (10 15859.7285067873
5531.6742081448 0.0) (11 15859.7285067873 3800.9049773756 0.0))
((0 . "LINE") (100 . "AcDbEntity") (8 . "LOUVERS") (62 . 7) (370 . 13) (100 . "AcDbLine") (10 15859.7285067873
3800.9049773756 0.0) (11 15831.9570135747 3800.9049773756 0.0))
((0 . "LINE") (100 . "AcDbEntity") (8 . "LOUVERS") (62 . 7) (370 . 13) (100 . "AcDbLine") (10 15831.9570135747
3800.9049773756 0.0) (11 15775.2941176471 3800.9049773756 0.0))
((0 . "LINE") (100 . "AcDbEntity") (8 . "LOUVERS") (62 . 7) (370 . 13) (100 . "AcDbLine") (10 15775.2941176471
3800.9049773756 0.0) (11 15748.834841629 3800.9049773756 0.0))
((0 . "LINE") (100 . "AcDbEntity") (8 . "LOUVERS") (62 . 7) (370 . 13) (100 . "AcDbLine") (10 15748.834841629
3800.9049773756 0.0) (11 15698.7330316742 3800.9049773756 0.0))
((0 . "LINE") (100 . "AcDbEntity") (8 . "LOUVERS") (62 . 7) (370 . 13) (100 . "AcDbLine") (10 15698.7330316742
3800.9049773756 0.0) (11 15681.3461538462 3800.9049773756 0.0))
((0 . "LINE") (100 . "AcDbEntity") (8 . "LOUVERS") (62 . 7) (370 . 13) (100 . "AcDbLine") (10 15681.3461538462
3800.9049773756 0.0) (11 15618.9479638009 3800.9049773756 0.0))
((0 . "LINE") (100 . "AcDbEntity") (8 . "LOUVERS") (62 . 7) (370 . 13) (100 . "AcDbLine") (10 15618.9479638009
3800.9049773756 0.0) (11 15568.1674208145 3800.9049773756 0.0))
((0 . "LINE") (100 . "AcDbEntity") (8 . "LOUVERS") (62 . 7) (370 . 13) (100 . "AcDbLine") (10 15568.1674208145
3800.9049773756 0.0) (11 15516.2895927602 3800.9049773756 0.0))
((0 . "LINE") (100 . "AcDbEntity") (8 . "LOUVERS") (62 . 7) (370 . 13) (100 . "AcDbLine") (10 15516.2895927602
3800.9049773756 0.0) (11 15498.5972850679 3800.9049773756 0.0))
((0 . "LINE") (100 . "AcDbEntity") (8 . "LOUVERS") (62 . 7) (370 . 13) (100 . "AcDbLine") (10 15498.5972850679
3800.9049773756 0.0) (11 15438.7104072398 3800.9049773756 0.0))
((0 . "LINE") (100 . "AcDbEntity") (8 . "LOUVERS") (62 . 7) (370 . 13) (100 . "AcDbLine") (10 15438.7104072398
3800.9049773756 0.0) (11 15421.685520362 3800.9049773756 0.0))
((0 . "LINE") (100 . "AcDbEntity") (8 . "LOUVERS") (62 . 7) (370 . 13) (100 . "AcDbLine") (10 15421.685520362
3800.9049773756 0.0) (11 15361.9909502262 3800.9049773756 0.0))
((0 . "LINE") (100 . "AcDbEntity") (8 . "WINDOWS") (62 . 7) (370 . 13) (100 . "AcDbLine") (10 15361.9909502262
3800.9049773756 0.0) (11 15361.9909502262 5045.2488687783 0.0))
((0 . "LINE") (100 . "AcDbEntity") (8 . "LOUVERS") (62 . 7) (370 . 13) (100 . "AcDbLine") (10 15361.9909502262
5045.2488687783 0.0) (11 15361.9909502262 5531.6742081448 0.0))
((0 . "LINE") (100 . "AcDbEntity") (8 . "LOUVERS") (62 . 7) (370 . 13) (100 . "AcDbLine") (10 15421.685520362
5531.6742081448 0.0) (11 15421.685520362 3800.9049773756 0.0))
((0 . "LINE") (100 . "AcDbEntity") (8 . "LOUVERS") (62 . 7) (370 . 13) (100 . "AcDbLine") (10 15438.7104072398
5531.6742081448 0.0) (11 15438.7104072398 3800.9049773756 0.0))
((0 . "LINE") (100 . "AcDbEntity") (8 . "LOUVERS") (62 . 7) (370 . 13) (100 . "AcDbLine") (10 15498.5972850679
5531.6742081448 0.0) (11 15498.5972850679 3800.9049773756 0.0))
((0 . "LINE") (100 . "AcDbEntity") (8 . "LOUVERS") (62 . 7) (370 . 13) (100 . "AcDbLine") (10 15516.2895927602
5531.6742081448 0.0) (11 15516.2895927602 3800.9049773756 0.0))
((0 . "LINE") (100 . "AcDbEntity") (8 . "LOUVERS") (62 . 7) (370 . 13) (100 . "AcDbLine") (10 15568.1674208145
5531.6742081448 0.0) (11 15568.1674208145 3800.9049773756 0.0))
((0 . "LINE") (100 . "AcDbEntity") (8 . "LOUVERS") (62 . 7) (370 . 13) (100 . "AcDbLine") (10 15618.9479638009
5531.6742081448 0.0) (11 15618.9479638009 3800.9049773756 0.0))
((0 . "LINE") (100 . "AcDbEntity") (8 . "LOUVERS") (62 . 7) (370 . 13) (100 . "AcDbLine") (10 15681.3461538462
5531.6742081448 0.0) (11 15681.3461538462 3800.9049773756 0.0))
((0 . "LINE") (100 . "AcDbEntity") (8 . "LOUVERS") (62 . 7) (370 . 13) (100 . "AcDbLine") (10 15698.7330316742
5531.6742081448 0.0) (11 15698.7330316742 3800.9049773756 0.0))
((0 . "LINE") (100 . "AcDbEntity") (8 . "LOUVERS") (62 . 7) (370 . 13) (100 . "AcDbLine") (10 15748.834841629
5531.6742081448 0.0) (11 15748.834841629 3800.9049773756 0.0))
((0 . "LINE") (100 . "AcDbEntity") (8 . "LOUVERS") (62 . 7) (370 . 13) (100 . "AcDbLine") (10 15775.2941176471
5531.6742081448 0.0) (11 15775.2941176471 3800.9049773756 0.0))
((0 . "LINE") (100 . "AcDbEntity") (8 . "LOUVERS") (62 . 7) (370 . 13) (100 . "AcDbLine") (10 15831.9570135747
5531.6742081448 0.0) (11 15831.9570135747 3800.9049773756 0.0))
((0 . "LINE") (100 . "AcDbEntity") (8 . "LOUVERS") (62 . 7) (370 . 13) (100 . "AcDbLine") (10 12420.814479638
5712.6696832579 0.0) (11 12478.4162895928 5712.6696832579 0.0))
((0 . "LINE") (100 . "AcDbEntity") (8 . "LOUVERS") (62 . 7) (370 . 13) (100 . "AcDbLine") (10 12478.4162895928
5712.6696832579 0.0) (11 12505.7918552036 5712.6696832579 0.0))
((0 . "LINE") (100 . "AcDbEntity") (8 . "LOUVERS") (62 . 7) (370 . 13) (100 . "AcDbLine") (10 12505.7918552036
5712.6696832579 0.0) (11 12552.0022624434 5712.6696832579 0.0))
((0 . "LINE") (100 . "AcDbEntity") (8 . "LOUVERS") (62 . 7) (370 . 13) (100 . "AcDbLine") (10 12552.0022624434
5712.6696832579 0.0) (11 12642.3076923077 5712.6696832579 0.0))
((0 . "LINE") (100 . "AcDbEntity") (8 . "LOUVERS") (62 . 7) (370 . 13) (100 . "AcDbLine") (10 12642.3076923077
5712.6696832579 0.0) (11 12695.1583710407 5712.6696832579 0.0))
((0 . "LINE") (100 . "AcDbEntity") (8 . "LOUVERS") (62 . 7) (370 . 13) (100 . "AcDbLine") (10 12695.1583710407
5712.6696832579 0.0) (11 12711.742081448 5712.6696832579 0.0))
((0 . "LINE") (100 . "AcDbEntity") (8 . "LOUVERS") (62 . 7) (370 . 13) (100 . "AcDbLine") (10 12711.742081448
5712.6696832579 0.0) (11 12761.2556561086 5712.6696832579 0.0))
((0 . "LINE") (100 . "AcDbEntity") (8 . "LOUVERS") (62 . 7) (370 . 13) (100 . "AcDbLine") (10 12761.2556561086
5712.6696832579 0.0) (11 12790.3054298643 5712.6696832579 0.0))
((0 . "LINE") (100 . "AcDbEntity") (8 . "LOUVERS") (62 . 7) (370 . 13) (100 . "AcDbLine") (10 12790.3054298643
5712.6696832579 0.0) (11 12820.2941176471 5712.6696832579 0.0))
((0 . "LINE") (100 . "AcDbEntity") (8 . "LOUVERS") (62 . 7) (370 . 13) (100 . "AcDbLine") (10 12820.2941176471
5712.6696832579 0.0) (11 12864.592760181 5712.6696832579 0.0))
((0 . "LINE") (100 . "AcDbEntity") (8 . "LOUVERS") (62 . 7) (370 . 13) (100 . "AcDbLine") (10 12864.592760181
5712.6696832579 0.0) (11 12883.3936651584 5712.6696832579 0.0))
((0 . "LINE") (100 . "AcDbEntity") (8 . "LOUVERS") (62 . 7) (370 . 13) (100 . "AcDbLine") (10 12883.3936651584
5712.6696832579 0.0) (11 12940.6787330317 5712.6696832579 0.0))
((0 . "LINE") (100 . "AcDbEntity") (8 . "LOUVERS") (62 . 7) (370 . 13) (100 . "AcDbLine") (10 12940.6787330317
5712.6696832579 0.0) (11 12952.4886877828 5712.6696832579 0.0))
((0 . "LINE") (100 . "AcDbEntity") (8 . "LOUVERS") (62 . 7) (370 . 13) (100 . "AcDbLine") (10 12952.4886877828
5712.6696832579 0.0) (11 12952.4886877828 5610.8597285068 0.0))
((0 . "LINE") (100 . "AcDbEntity") (8 . "LOUVERS") (62 . 7) (370 . 13) (100 . "AcDbLine") (10 12952.4886877828
5610.8597285068 0.0) (11 12952.4886877828 3800.9049773756 0.0))
((0 . "LINE") (100 . "AcDbEntity") (8 . "LOUVERS") (62 . 7) (370 . 13) (100 . "AcDbLine") (10 12952.4886877828
3800.9049773756 0.0) (11 12940.6787330317 3800.9049773756 0.0))
((0 . "LINE") (100 . "AcDbEntity") (8 . "LOUVERS") (62 . 7) (370 . 13) (100 . "AcDbLine") (10 12940.6787330317
3800.9049773756 0.0) (11 12883.3936651584 3800.9049773756 0.0))
((0 . "LINE") (100 . "AcDbEntity") (8 . "LOUVERS") (62 . 7) (370 . 13) (100 . "AcDbLine") (10 12883.3936651584
3800.9049773756 0.0) (11 12864.592760181 3800.9049773756 0.0))
((0 . "LINE") (100 . "AcDbEntity") (8 . "LOUVERS") (62 . 7) (370 . 13) (100 . "AcDbLine") (10 12864.592760181
3800.9049773756 0.0) (11 12820.2941176471 3800.9049773756 0.0))
((0 . "LINE") (100 . "AcDbEntity") (8 . "LOUVERS") (62 . 7) (370 . 13) (100 . "AcDbLine") (10 12820.2941176471
3800.9049773756 0.0) (11 12790.3054298643 3800.9049773756 0.0))
((0 . "LINE") (100 . "AcDbEntity") (8 . "LOUVERS") (62 . 7) (370 . 13) (100 . "AcDbLine") (10 12790.3054298643
3800.9049773756 0.0) (11 12761.2556561086 3800.9049773756 0.0))
((0 . "LINE") (100 . "AcDbEntity") (8 . "LOUVERS") (62 . 7) (370 . 13) (100 . "AcDbLine") (10 12761.2556561086
3800.9049773756 0.0) (11 12711.742081448 3800.9049773756 0.0))
((0 . "LINE") (100 . "AcDbEntity") (8 . "LOUVERS") (62 . 7) (370 . 13) (100 . "AcDbLine") (10 12711.742081448
3800.9049773756 0.0) (11 12695.1583710407 3800.9049773756 0.0))
((0 . "LINE") (100 . "AcDbEntity") (8 . "LOUVERS") (62 . 7) (370 . 13) (100 . "AcDbLine") (10 12695.1583710407
3800.9049773756 0.0) (11 12642.3076923077 3800.9049773756 0.0))
((0 . "LINE") (100 . "AcDbEntity") (8 . "LOUVERS") (62 . 7) (370 . 13) (100 . "AcDbLine") (10 12642.3076923077
3800.9049773756 0.0) (11 12552.0022624434 3800.9049773756 0.0))
((0 . "LINE") (100 . "AcDbEntity") (8 . "LOUVERS") (62 . 7) (370 . 13) (100 . "AcDbLine") (10 12552.0022624434
3800.9049773756 0.0) (11 12505.7918552036 3800.9049773756 0.0))
((0 . "LINE") (100 . "AcDbEntity") (8 . "LOUVERS") (62 . 7) (370 . 13) (100 . "AcDbLine") (10 12505.7918552036
3800.9049773756 0.0) (11 12478.4162895928 3800.9049773756 0.0))
((0 . "LINE") (100 . "AcDbEntity") (8 . "LOUVERS") (62 . 7) (370 . 13) (100 . "AcDbLine") (10 12478.4162895928
3800.9049773756 0.0) (11 12420.814479638 3800.9049773756 0.0))
((0 . "LINE") (100 . "AcDbEntity") (8 . "LOUVERS") (62 . 7) (370 . 13) (100 . "AcDbLine") (10 12420.814479638
3800.9049773756 0.0) (11 12420.814479638 5610.8597285068 0.0))
((0 . "LINE") (100 . "AcDbEntity") (8 . "LOUVERS") (62 . 7) (370 . 13) (100 . "AcDbLine") (10 12420.814479638
5610.8597285068 0.0) (11 12420.814479638 5712.6696832579 0.0))
((0 . "LINE") (100 . "AcDbEntity") (8 . "LOUVERS") (62 . 7) (370 . 13) (100 . "AcDbLine") (10 12478.4162895928
5712.6696832579 0.0) (11 12478.4162895928 5610.8597285068 0.0))
((0 . "LINE") (100 . "AcDbEntity") (8 . "LOUVERS") (62 . 7) (370 . 13) (100 . "AcDbLine") (10 12478.4162895928
5610.8597285068 0.0) (11 12478.4162895928 3800.9049773756 0.0))
((0 . "LINE") (100 . "AcDbEntity") (8 . "LOUVERS") (62 . 7) (370 . 13) (100 . "AcDbLine") (10 12505.7918552036
5712.6696832579 0.0) (11 12505.7918552036 5610.8597285068 0.0))
((0 . "LINE") (100 . "AcDbEntity") (8 . "LOUVERS") (62 . 7) (370 . 13) (100 . "AcDbLine") (10 12505.7918552036
5610.8597285068 0.0) (11 12505.7918552036 3800.9049773756 0.0))
((0 . "LINE") (100 . "AcDbEntity") (8 . "LOUVERS") (62 . 7) (370 . 13) (100 . "AcDbLine") (10 12552.0022624434
5712.6696832579 0.0) (11 12552.0022624434 5610.8597285068 0.0))
((0 . "LINE") (100 . "AcDbEntity") (8 . "LOUVERS") (62 . 7) (370 . 13) (100 . "AcDbLine") (10 12552.0022624434
5610.8597285068 0.0) (11 12552.0022624434 3800.9049773756 0.0))
((0 . "LINE") (100 . "AcDbEntity") (8 . "LOUVERS") (62 . 7) (370 . 13) (100 . "AcDbLine") (10 12642.3076923077
5712.6696832579 0.0) (11 12642.3076923077 5610.8597285068 0.0))
((0 . "LINE") (100 . "AcDbEntity") (8 . "LOUVERS") (62 . 7) (370 . 13) (100 . "AcDbLine") (10 12642.3076923077
5610.8597285068 0.0) (11 12642.3076923077 3800.9049773756 0.0))
((0 . "LINE") (100 . "AcDbEntity") (8 . "LOUVERS") (62 . 7) (370 . 13) (100 . "AcDbLine") (10 12695.1583710407
5712.6696832579 0.0) (11 12695.1583710407 5610.8597285068 0.0))
((0 . "LINE") (100 . "AcDbEntity") (8 . "LOUVERS") (62 . 7) (370 . 13) (100 . "AcDbLine") (10 12695.1583710407
5610.8597285068 0.0) (11 12695.1583710407 3800.9049773756 0.0))
((0 . "LINE") (100 . "AcDbEntity") (8 . "LOUVERS") (62 . 7) (370 . 13) (100 . "AcDbLine") (10 12711.742081448
5712.6696832579 0.0) (11 12711.742081448 5610.8597285068 0.0))
((0 . "LINE") (100 . "AcDbEntity") (8 . "LOUVERS") (62 . 7) (370 . 13) (100 . "AcDbLine") (10 12711.742081448
5610.8597285068 0.0) (11 12711.742081448 3800.9049773756 0.0))
((0 . "LINE") (100 . "AcDbEntity") (8 . "LOUVERS") (62 . 7) (370 . 13) (100 . "AcDbLine") (10 12761.2556561086
5712.6696832579 0.0) (11 12761.2556561086 5610.8597285068 0.0))
((0 . "LINE") (100 . "AcDbEntity") (8 . "LOUVERS") (62 . 7) (370 . 13) (100 . "AcDbLine") (10 12761.2556561086
5610.8597285068 0.0) (11 12761.2556561086 3800.9049773756 0.0))
((0 . "LINE") (100 . "AcDbEntity") (8 . "LOUVERS") (62 . 7) (370 . 13) (100 . "AcDbLine") (10 12790.3054298643
5712.6696832579 0.0) (11 12790.3054298643 5610.8597285068 0.0))
((0 . "LINE") (100 . "AcDbEntity") (8 . "LOUVERS") (62 . 7) (370 . 13) (100 . "AcDbLine") (10 12790.3054298643
5610.8597285068 0.0) (11 12790.3054298643 3800.9049773756 0.0))
((0 . "LINE") (100 . "AcDbEntity") (8 . "LOUVERS") (62 . 7) (370 . 13) (100 . "AcDbLine") (10 12820.2941176471
5712.6696832579 0.0) (11 12820.2941176471 5610.8597285068 0.0))
((0 . "LINE") (100 . "AcDbEntity") (8 . "LOUVERS") (62 . 7) (370 . 13) (100 . "AcDbLine") (10 12820.2941176471
5610.8597285068 0.0) (11 12820.2941176471 3800.9049773756 0.0))
((0 . "LINE") (100 . "AcDbEntity") (8 . "LOUVERS") (62 . 7) (370 . 13) (100 . "AcDbLine") (10 12864.592760181
5712.6696832579 0.0) (11 12864.592760181 5610.8597285068 0.0))
((0 . "LINE") (100 . "AcDbEntity") (8 . "LOUVERS") (62 . 7) (370 . 13) (100 . "AcDbLine") (10 12864.592760181
5610.8597285068 0.0) (11 12864.592760181 3800.9049773756 0.0))
((0 . "LINE") (100 . "AcDbEntity") (8 . "LOUVERS") (62 . 7) (370 . 13) (100 . "AcDbLine") (10 12883.3936651584
5712.6696832579 0.0) (11 12883.3936651584 5610.8597285068 0.0))
((0 . "LINE") (100 . "AcDbEntity") (8 . "LOUVERS") (62 . 7) (370 . 13) (100 . "AcDbLine") (10 12883.3936651584
5610.8597285068 0.0) (11 12883.3936651584 3800.9049773756 0.0))
((0 . "LINE") (100 . "AcDbEntity") (8 . "LOUVERS") (62 . 7) (370 . 13) (100 . "AcDbLine") (10 12940.6787330317
5712.6696832579 0.0) (11 12940.6787330317 5610.8597285068 0.0))
((0 . "LINE") (100 . "AcDbEntity") (8 . "LOUVERS") (62 . 7) (370 . 13) (100 . "AcDbLine") (10 12940.6787330317
5610.8597285068 0.0) (11 12940.6787330317 3800.9049773756 0.0))
((0 . "LINE") (100 . "AcDbEntity") (8 . "LOUVERS") (62 . 7) (370 . 13) (100 . "AcDbLine") (10 16221.7194570136
5712.6696832579 0.0) (11 16274.2986425339 5712.6696832579 0.0))
((0 . "LINE") (100 . "AcDbEntity") (8 . "LOUVERS") (62 . 7) (370 . 13) (100 . "AcDbLine") (10 16274.2986425339
5712.6696832579 0.0) (11 16301.6063348416 5712.6696832579 0.0))
((0 . "LINE") (100 . "AcDbEntity") (8 . "LOUVERS") (62 . 7) (370 . 13) (100 . "AcDbLine") (10 16301.6063348416
5712.6696832579 0.0) (11 16348.3823529412 5712.6696832579 0.0))
((0 . "LINE") (100 . "AcDbEntity") (8 . "LOUVERS") (62 . 7) (370 . 13) (100 . "AcDbLine") (10 16348.3823529412
5712.6696832579 0.0) (11 16375.4524886878 5712.6696832579 0.0))
((0 . "LINE") (100 . "AcDbEntity") (8 . "LOUVERS") (62 . 7) (370 . 13) (100 . "AcDbLine") (10 16375.4524886878
5712.6696832579 0.0) (11 16442.3076923077 5712.6696832579 0.0))
((0 . "LINE") (100 . "AcDbEntity") (8 . "LOUVERS") (62 . 7) (370 . 13) (100 . "AcDbLine") (10 16442.3076923077
5712.6696832579 0.0) (11 16504.536199095 5712.6696832579 0.0))
((0 . "LINE") (100 . "AcDbEntity") (8 . "LOUVERS") (62 . 7) (370 . 13) (100 . "AcDbLine") (10 16504.536199095
5712.6696832579 0.0) (11 16540.9389140272 5712.6696832579 0.0))
((0 . "LINE") (100 . "AcDbEntity") (8 . "LOUVERS") (62 . 7) (370 . 13) (100 . "AcDbLine") (10 16540.9389140272
5712.6696832579 0.0) (11 16576.6742081448 5712.6696832579 0.0))
((0 . "LINE") (100 . "AcDbEntity") (8 . "LOUVERS") (62 . 7) (370 . 13) (100 . "AcDbLine") (10 16576.6742081448
5712.6696832579 0.0) (11 16625.5769230769 5712.6696832579 0.0))
((0 . "LINE") (100 . "AcDbEntity") (8 . "LOUVERS") (62 . 7) (370 . 13) (100 . "AcDbLine") (10 16625.5769230769
5712.6696832579 0.0) (11 16650.9389140271 5712.6696832579 0.0))
((0 . "LINE") (100 . "AcDbEntity") (8 . "LOUVERS") (62 . 7) (370 . 13) (100 . "AcDbLine") (10 16650.9389140271
5712.6696832579 0.0) (11 16696.1538461538 5712.6696832579 0.0))
((0 . "LINE") (100 . "AcDbEntity") (8 . "LOUVERS") (62 . 7) (370 . 13) (100 . "AcDbLine") (10 16696.1538461538
5712.6696832579 0.0) (11 16725.350678733 5712.6696832579 0.0))
((0 . "LINE") (100 . "AcDbEntity") (8 . "LOUVERS") (62 . 7) (370 . 13) (100 . "AcDbLine") (10 16725.350678733
5712.6696832579 0.0) (11 16773.7556561086 5712.6696832579 0.0))
((0 . "LINE") (100 . "AcDbEntity") (8 . "LOUVERS") (62 . 7) (370 . 13) (100 . "AcDbLine") (10 16773.7556561086
5712.6696832579 0.0) (11 16787.3303167421 5712.6696832579 0.0))
((0 . "LINE") (100 . "AcDbEntity") (8 . "LOUVERS") (62 . 7) (370 . 13) (100 . "AcDbLine") (10 16787.3303167421
5712.6696832579 0.0) (11 16787.3303167421 5610.8597285068 0.0))
((0 . "LINE") (100 . "AcDbEntity") (8 . "LOUVERS") (62 . 7) (370 . 13) (100 . "AcDbLine") (10 16787.3303167421
5610.8597285068 0.0) (11 16787.3303167421 3800.9049773756 0.0))
((0 . "LINE") (100 . "AcDbEntity") (8 . "LOUVERS") (62 . 7) (370 . 13) (100 . "AcDbLine") (10 16787.3303167421
3800.9049773756 0.0) (11 16773.7556561086 3800.9049773756 0.0))
((0 . "LINE") (100 . "AcDbEntity") (8 . "LOUVERS") (62 . 7) (370 . 13) (100 . "AcDbLine") (10 16773.7556561086
3800.9049773756 0.0) (11 16725.350678733 3800.9049773756 0.0))
((0 . "LINE") (100 . "AcDbEntity") (8 . "LOUVERS") (62 . 7) (370 . 13) (100 . "AcDbLine") (10 16725.350678733
3800.9049773756 0.0) (11 16696.1538461538 3800.9049773756 0.0))
((0 . "LINE") (100 . "AcDbEntity") (8 . "LOUVERS") (62 . 7) (370 . 13) (100 . "AcDbLine") (10 16696.1538461538
3800.9049773756 0.0) (11 16650.9389140271 3800.9049773756 0.0))
((0 . "LINE") (100 . "AcDbEntity") (8 . "LOUVERS") (62 . 7) (370 . 13) (100 . "AcDbLine") (10 16650.9389140271
3800.9049773756 0.0) (11 16625.5769230769 3800.9049773756 0.0))
((0 . "LINE") (100 . "AcDbEntity") (8 . "LOUVERS") (62 . 7) (370 . 13) (100 . "AcDbLine") (10 16625.5769230769
3800.9049773756 0.0) (11 16576.6742081448 3800.9049773756 0.0))
((0 . "LINE") (100 . "AcDbEntity") (8 . "LOUVERS") (62 . 7) (370 . 13) (100 . "AcDbLine") (10 16576.6742081448
3800.9049773756 0.0) (11 16540.9389140272 3800.9049773756 0.0))
((0 . "LINE") (100 . "AcDbEntity") (8 . "LOUVERS") (62 . 7) (370 . 13) (100 . "AcDbLine") (10 16540.9389140272
3800.9049773756 0.0) (11 16504.536199095 3800.9049773756 0.0))
((0 . "LINE") (100 . "AcDbEntity") (8 . "LOUVERS") (62 . 7) (370 . 13) (100 . "AcDbLine") (10 16504.536199095
3800.9049773756 0.0) (11 16442.3076923077 3800.9049773756 0.0))
((0 . "LINE") (100 . "AcDbEntity") (8 . "LOUVERS") (62 . 7) (370 . 13) (100 . "AcDbLine") (10 16442.3076923077
3800.9049773756 0.0) (11 16375.4524886878 3800.9049773756 0.0))
((0 . "LINE") (100 . "AcDbEntity") (8 . "LOUVERS") (62 . 7) (370 . 13) (100 . "AcDbLine") (10 16375.4524886878
3800.9049773756 0.0) (11 16348.3823529412 3800.9049773756 0.0))
((0 . "LINE") (100 . "AcDbEntity") (8 . "LOUVERS") (62 . 7) (370 . 13) (100 . "AcDbLine") (10 16348.3823529412
3800.9049773756 0.0) (11 16301.6063348416 3800.9049773756 0.0))
((0 . "LINE") (100 . "AcDbEntity") (8 . "LOUVERS") (62 . 7) (370 . 13) (100 . "AcDbLine") (10 16301.6063348416
3800.9049773756 0.0) (11 16274.2986425339 3800.9049773756 0.0))
((0 . "LINE") (100 . "AcDbEntity") (8 . "LOUVERS") (62 . 7) (370 . 13) (100 . "AcDbLine") (10 16274.2986425339
3800.9049773756 0.0) (11 16221.7194570136 3800.9049773756 0.0))
((0 . "LINE") (100 . "AcDbEntity") (8 . "LOUVERS") (62 . 7) (370 . 13) (100 . "AcDbLine") (10 16221.7194570136
3800.9049773756 0.0) (11 16221.7194570136 5610.8597285068 0.0))
((0 . "LINE") (100 . "AcDbEntity") (8 . "LOUVERS") (62 . 7) (370 . 13) (100 . "AcDbLine") (10 16221.7194570136
5610.8597285068 0.0) (11 16221.7194570136 5712.6696832579 0.0))
((0 . "LINE") (100 . "AcDbEntity") (8 . "LOUVERS") (62 . 7) (370 . 13) (100 . "AcDbLine") (10 16274.2986425339
5712.6696832579 0.0) (11 16274.2986425339 5610.8597285068 0.0))
((0 . "LINE") (100 . "AcDbEntity") (8 . "LOUVERS") (62 . 7) (370 . 13) (100 . "AcDbLine") (10 16274.2986425339
5610.8597285068 0.0) (11 16274.2986425339 3800.9049773756 0.0))
((0 . "LINE") (100 . "AcDbEntity") (8 . "LOUVERS") (62 . 7) (370 . 13) (100 . "AcDbLine") (10 16301.6063348416
5712.6696832579 0.0) (11 16301.6063348416 5610.8597285068 0.0))
((0 . "LINE") (100 . "AcDbEntity") (8 . "LOUVERS") (62 . 7) (370 . 13) (100 . "AcDbLine") (10 16301.6063348416
5610.8597285068 0.0) (11 16301.6063348416 3800.9049773756 0.0))
((0 . "LINE") (100 . "AcDbEntity") (8 . "LOUVERS") (62 . 7) (370 . 13) (100 . "AcDbLine") (10 16348.3823529412
5712.6696832579 0.0) (11 16348.3823529412 5610.8597285068 0.0))
((0 . "LINE") (100 . "AcDbEntity") (8 . "LOUVERS") (62 . 7) (370 . 13) (100 . "AcDbLine") (10 16348.3823529412
5610.8597285068 0.0) (11 16348.3823529412 3800.9049773756 0.0))
((0 . "LINE") (100 . "AcDbEntity") (8 . "LOUVERS") (62 . 7) (370 . 13) (100 . "AcDbLine") (10 16375.4524886878
5712.6696832579 0.0) (11 16375.4524886878 5610.8597285068 0.0))
((0 . "LINE") (100 . "AcDbEntity") (8 . "LOUVERS") (62 . 7) (370 . 13) (100 . "AcDbLine") (10 16375.4524886878
5610.8597285068 0.0) (11 16375.4524886878 3800.9049773756 0.0))
((0 . "LINE") (100 . "AcDbEntity") (8 . "LOUVERS") (62 . 7) (370 . 13) (100 . "AcDbLine") (10 16442.3076923077
5712.6696832579 0.0) (11 16442.3076923077 5610.8597285068 0.0))
((0 . "LINE") (100 . "AcDbEntity") (8 . "LOUVERS") (62 . 7) (370 . 13) (100 . "AcDbLine") (10 16442.3076923077
5610.8597285068 0.0) (11 16442.3076923077 3800.9049773756 0.0))
((0 . "LINE") (100 . "AcDbEntity") (8 . "LOUVERS") (62 . 7) (370 . 13) (100 . "AcDbLine") (10 16504.536199095
5712.6696832579 0.0) (11 16504.536199095 5610.8597285068 0.0))
((0 . "LINE") (100 . "AcDbEntity") (8 . "LOUVERS") (62 . 7) (370 . 13) (100 . "AcDbLine") (10 16504.536199095
5610.8597285068 0.0) (11 16504.536199095 3800.9049773756 0.0))
((0 . "LINE") (100 . "AcDbEntity") (8 . "LOUVERS") (62 . 7) (370 . 13) (100 . "AcDbLine") (10 16540.9389140272
5712.6696832579 0.0) (11 16540.9389140272 5610.8597285068 0.0))
((0 . "LINE") (100 . "AcDbEntity") (8 . "LOUVERS") (62 . 7) (370 . 13) (100 . "AcDbLine") (10 16540.9389140272
5610.8597285068 0.0) (11 16540.9389140272 3800.9049773756 0.0))
((0 . "LINE") (100 . "AcDbEntity") (8 . "LOUVERS") (62 . 7) (370 . 13) (100 . "AcDbLine") (10 16576.6742081448
5712.6696832579 0.0) (11 16576.6742081448 5610.8597285068 0.0))
((0 . "LINE") (100 . "AcDbEntity") (8 . "LOUVERS") (62 . 7) (370 . 13) (100 . "AcDbLine") (10 16576.6742081448
5610.8597285068 0.0) (11 16576.6742081448 3800.9049773756 0.0))
((0 . "LINE") (100 . "AcDbEntity") (8 . "LOUVERS") (62 . 7) (370 . 13) (100 . "AcDbLine") (10 16625.5769230769
5712.6696832579 0.0) (11 16625.5769230769 5610.8597285068 0.0))
((0 . "LINE") (100 . "AcDbEntity") (8 . "LOUVERS") (62 . 7) (370 . 13) (100 . "AcDbLine") (10 16625.5769230769
5610.8597285068 0.0) (11 16625.5769230769 3800.9049773756 0.0))
((0 . "LINE") (100 . "AcDbEntity") (8 . "LOUVERS") (62 . 7) (370 . 13) (100 . "AcDbLine") (10 16650.9389140271
5712.6696832579 0.0) (11 16650.9389140271 5610.8597285068 0.0))
((0 . "LINE") (100 . "AcDbEntity") (8 . "LOUVERS") (62 . 7) (370 . 13) (100 . "AcDbLine") (10 16650.9389140271
5610.8597285068 0.0) (11 16650.9389140271 3800.9049773756 0.0))
((0 . "LINE") (100 . "AcDbEntity") (8 . "LOUVERS") (62 . 7) (370 . 13) (100 . "AcDbLine") (10 16696.1538461538
5712.6696832579 0.0) (11 16696.1538461538 5610.8597285068 0.0))
((0 . "LINE") (100 . "AcDbEntity") (8 . "LOUVERS") (62 . 7) (370 . 13) (100 . "AcDbLine") (10 16696.1538461538
5610.8597285068 0.0) (11 16696.1538461538 3800.9049773756 0.0))
((0 . "LINE") (100 . "AcDbEntity") (8 . "LOUVERS") (62 . 7) (370 . 13) (100 . "AcDbLine") (10 16725.350678733
5712.6696832579 0.0) (11 16725.350678733 5610.8597285068 0.0))
((0 . "LINE") (100 . "AcDbEntity") (8 . "LOUVERS") (62 . 7) (370 . 13) (100 . "AcDbLine") (10 16725.350678733
5610.8597285068 0.0) (11 16725.350678733 3800.9049773756 0.0))
((0 . "LINE") (100 . "AcDbEntity") (8 . "LOUVERS") (62 . 7) (370 . 13) (100 . "AcDbLine") (10 16773.7556561086
5712.6696832579 0.0) (11 16773.7556561086 5610.8597285068 0.0))
((0 . "LINE") (100 . "AcDbEntity") (8 . "LOUVERS") (62 . 7) (370 . 13) (100 . "AcDbLine") (10 16773.7556561086
5610.8597285068 0.0) (11 16773.7556561086 3800.9049773756 0.0))
((0 . "LINE") (100 . "AcDbEntity") (8 . "LOUVERS") (62 . 7) (370 . 13) (100 . "AcDbLine") (10 13212.6696832579
3212.6696832579 0.0) (11 13246.8778280543 3212.6696832579 0.0))
((0 . "LINE") (100 . "AcDbEntity") (8 . "LOUVERS") (62 . 7) (370 . 13) (100 . "AcDbLine") (10 13246.8778280543
3212.6696832579 0.0) (11 13296.2895927602 3212.6696832579 0.0))
((0 . "LINE") (100 . "AcDbEntity") (8 . "LOUVERS") (62 . 7) (370 . 13) (100 . "AcDbLine") (10 13296.2895927602
3212.6696832579 0.0) (11 13333.257918552 3212.6696832579 0.0))
((0 . "LINE") (100 . "AcDbEntity") (8 . "LOUVERS") (62 . 7) (370 . 13) (100 . "AcDbLine") (10 13333.257918552
3212.6696832579 0.0) (11 13379.1628959276 3212.6696832579 0.0))
((0 . "LINE") (100 . "AcDbEntity") (8 . "LOUVERS") (62 . 7) (370 . 13) (100 . "AcDbLine") (10 13379.1628959276
3212.6696832579 0.0) (11 13416.2895927602 3212.6696832579 0.0))
((0 . "LINE") (100 . "AcDbEntity") (8 . "LOUVERS") (62 . 7) (370 . 13) (100 . "AcDbLine") (10 13416.2895927602
3212.6696832579 0.0) (11 13451.7307692308 3212.6696832579 0.0))
((0 . "LINE") (100 . "AcDbEntity") (8 . "LOUVERS") (62 . 7) (370 . 13) (100 . "AcDbLine") (10 13451.7307692308
3212.6696832579 0.0) (11 13498.2918552036 3212.6696832579 0.0))
((0 . "LINE") (100 . "AcDbEntity") (8 . "LOUVERS") (62 . 7) (370 . 13) (100 . "AcDbLine") (10 13498.2918552036
3212.6696832579 0.0) (11 13531.221719457 3212.6696832579 0.0))
((0 . "LINE") (100 . "AcDbEntity") (8 . "LOUVERS") (62 . 7) (370 . 13) (100 . "AcDbLine") (10 13531.221719457
3212.6696832579 0.0) (11 13570.4411764706 3212.6696832579 0.0))
((0 . "LINE") (100 . "AcDbEntity") (8 . "LOUVERS") (62 . 7) (370 . 13) (100 . "AcDbLine") (10 13570.4411764706
3212.6696832579 0.0) (11 13600.3959276018 3212.6696832579 0.0))
((0 . "LINE") (100 . "AcDbEntity") (8 . "LOUVERS") (62 . 7) (370 . 13) (100 . "AcDbLine") (10 13600.3959276018
3212.6696832579 0.0) (11 13641.4479638009 3212.6696832579 0.0))
((0 . "LINE") (100 . "AcDbEntity") (8 . "LOUVERS") (62 . 7) (370 . 13) (100 . "AcDbLine") (10 13641.4479638009
3212.6696832579 0.0) (11 13679.6832579186 3212.6696832579 0.0))
((0 . "LINE") (100 . "AcDbEntity") (8 . "LOUVERS") (62 . 7) (370 . 13) (100 . "AcDbLine") (10 13679.6832579186
3212.6696832579 0.0) (11 13722.0814479638 3212.6696832579 0.0))
((0 . "LINE") (100 . "AcDbEntity") (8 . "LOUVERS") (62 . 7) (370 . 13) (100 . "AcDbLine") (10 13722.0814479638
3212.6696832579 0.0) (11 13757.5113122172 3212.6696832579 0.0))
((0 . "LINE") (100 . "AcDbEntity") (8 . "LOUVERS") (62 . 7) (370 . 13) (100 . "AcDbLine") (10 13757.5113122172
3212.6696832579 0.0) (11 13791.9117647059 3212.6696832579 0.0))
((0 . "LINE") (100 . "AcDbEntity") (8 . "LOUVERS") (62 . 7) (370 . 13) (100 . "AcDbLine") (10 13791.9117647059
3212.6696832579 0.0) (11 13824.4796380091 3212.6696832579 0.0))
((0 . "LINE") (100 . "AcDbEntity") (8 . "LOUVERS") (62 . 7) (370 . 13) (100 . "AcDbLine") (10 13824.4796380091
3212.6696832579 0.0) (11 13857.6583710407 3212.6696832579 0.0))
((0 . "LINE") (100 . "AcDbEntity") (8 . "LOUVERS") (62 . 7) (370 . 13) (100 . "AcDbLine") (10 13857.6583710407
3212.6696832579 0.0) (11 13887.5791855204 3212.6696832579 0.0))
((0 . "LINE") (100 . "AcDbEntity") (8 . "LOUVERS") (62 . 7) (370 . 13) (100 . "AcDbLine") (10 13887.5791855204
3212.6696832579 0.0) (11 13923.5520361991 3212.6696832579 0.0))
((0 . "LINE") (100 . "AcDbEntity") (8 . "LOUVERS") (62 . 7) (370 . 13) (100 . "AcDbLine") (10 13923.5520361991
3212.6696832579 0.0) (11 13954.7850678733 3212.6696832579 0.0))
((0 . "LINE") (100 . "AcDbEntity") (8 . "LOUVERS") (62 . 7) (370 . 13) (100 . "AcDbLine") (10 13954.7850678733
3212.6696832579 0.0) (11 13991.7081447964 3212.6696832579 0.0))
((0 . "LINE") (100 . "AcDbEntity") (8 . "LOUVERS") (62 . 7) (370 . 13) (100 . "AcDbLine") (10 13991.7081447964
3212.6696832579 0.0) (11 14027.9298642534 3212.6696832579 0.0))
((0 . "LINE") (100 . "AcDbEntity") (8 . "LOUVERS") (62 . 7) (370 . 13) (100 . "AcDbLine") (10 14027.9298642534
3212.6696832579 0.0) (11 14082.8846153846 3212.6696832579 0.0))
((0 . "LINE") (100 . "AcDbEntity") (8 . "LOUVERS") (62 . 7) (370 . 13) (100 . "AcDbLine") (10 14082.8846153846
3212.6696832579 0.0) (11 14109.8190045249 3212.6696832579 0.0))
((0 . "LINE") (100 . "AcDbEntity") (8 . "LOUVERS") (62 . 7) (370 . 13) (100 . "AcDbLine") (10 14109.8190045249
3212.6696832579 0.0) (11 14142.7036199095 3212.6696832579 0.0))
((0 . "LINE") (100 . "AcDbEntity") (8 . "LOUVERS") (62 . 7) (370 . 13) (100 . "AcDbLine") (10 14142.7036199095
3212.6696832579 0.0) (11 14171.6968325792 3212.6696832579 0.0))
((0 . "LINE") (100 . "AcDbEntity") (8 . "LOUVERS") (62 . 7) (370 . 13) (100 . "AcDbLine") (10 14171.6968325792
3212.6696832579 0.0) (11 14209.5248868778 3212.6696832579 0.0))
((0 . "LINE") (100 . "AcDbEntity") (8 . "LOUVERS") (62 . 7) (370 . 13) (100 . "AcDbLine") (10 14209.5248868778
3212.6696832579 0.0) (11 14231.8552036199 3212.6696832579 0.0))
((0 . "LINE") (100 . "AcDbEntity") (8 . "LOUVERS") (62 . 7) (370 . 13) (100 . "AcDbLine") (10 14231.8552036199
3212.6696832579 0.0) (11 14279.1742081448 3212.6696832579 0.0))
((0 . "LINE") (100 . "AcDbEntity") (8 . "LOUVERS") (62 . 7) (370 . 13) (100 . "AcDbLine") (10 14279.1742081448
3212.6696832579 0.0) (11 14308.834841629 3212.6696832579 0.0))
((0 . "LINE") (100 . "AcDbEntity") (8 . "LOUVERS") (62 . 7) (370 . 13) (100 . "AcDbLine") (10 14308.834841629
3212.6696832579 0.0) (11 14347.5904977376 3212.6696832579 0.0))
((0 . "LINE") (100 . "AcDbEntity") (8 . "LOUVERS") (62 . 7) (370 . 13) (100 . "AcDbLine") (10 14347.5904977376
3212.6696832579 0.0) (11 14391.4366515837 3212.6696832579 0.0))
((0 . "LINE") (100 . "AcDbEntity") (8 . "LOUVERS") (62 . 7) (370 . 13) (100 . "AcDbLine") (10 14391.4366515837
3212.6696832579 0.0) (11 14408.2239819005 3212.6696832579 0.0))
((0 . "LINE") (100 . "AcDbEntity") (8 . "LOUVERS") (62 . 7) (370 . 13) (100 . "AcDbLine") (10 14408.2239819005
3212.6696832579 0.0) (11 14446.9343891403 3212.6696832579 0.0))
((0 . "LINE") (100 . "AcDbEntity") (8 . "LOUVERS") (62 . 7) (370 . 13) (100 . "AcDbLine") (10 14446.9343891403
3212.6696832579 0.0) (11 14466.5045248869 3212.6696832579 0.0))
((0 . "LINE") (100 . "AcDbEntity") (8 . "LOUVERS") (62 . 7) (370 . 13) (100 . "AcDbLine") (10 14466.5045248869
3212.6696832579 0.0) (11 14506.2443438914 3212.6696832579 0.0))
((0 . "LINE") (100 . "AcDbEntity") (8 . "LOUVERS") (62 . 7) (370 . 13) (100 . "AcDbLine") (10 14506.2443438914
3212.6696832579 0.0) (11 14522.2058823529 3212.6696832579 0.0))
((0 . "LINE") (100 . "AcDbEntity") (8 . "LOUVERS") (62 . 7) (370 . 13) (100 . "AcDbLine") (10 14522.2058823529
3212.6696832579 0.0) (11 14569.1742081448 3212.6696832579 0.0))
((0 . "LINE") (100 . "AcDbEntity") (8 . "LOUVERS") (62 . 7) (370 . 13) (100 . "AcDbLine") (10 14569.1742081448
3212.6696832579 0.0) (11 14608.0316742081 3212.6696832579 0.0))
((0 . "LINE") (100 . "AcDbEntity") (8 . "LOUVERS") (62 . 7) (370 . 13) (100 . "AcDbLine") (10 14608.0316742081
3212.6696832579 0.0) (11 14622.3416289593 3212.6696832579 0.0))
((0 . "LINE") (100 . "AcDbEntity") (8 . "LOUVERS") (62 . 7) (370 . 13) (100 . "AcDbLine") (10 14622.3416289593
3212.6696832579 0.0) (11 14658.3936651584 3212.6696832579 0.0))
((0 . "LINE") (100 . "AcDbEntity") (8 . "LOUVERS") (62 . 7) (370 . 13) (100 . "AcDbLine") (10 14658.3936651584
3212.6696832579 0.0) (11 14687.5113122172 3212.6696832579 0.0))
((0 . "LINE") (100 . "AcDbEntity") (8 . "LOUVERS") (62 . 7) (370 . 13) (100 . "AcDbLine") (10 14687.5113122172
3212.6696832579 0.0) (11 14734.3552036199 3212.6696832579 0.0))
((0 . "LINE") (100 . "AcDbEntity") (8 . "LOUVERS") (62 . 7) (370 . 13) (100 . "AcDbLine") (10 14734.3552036199
3212.6696832579 0.0) (11 14774.5475113122 3212.6696832579 0.0))
((0 . "LINE") (100 . "AcDbEntity") (8 . "LOUVERS") (62 . 7) (370 . 13) (100 . "AcDbLine") (10 14774.5475113122
3212.6696832579 0.0) (11 14802.0475113122 3212.6696832579 0.0))
((0 . "LINE") (100 . "AcDbEntity") (8 . "LOUVERS") (62 . 7) (370 . 13) (100 . "AcDbLine") (10 14802.0475113122
3212.6696832579 0.0) (11 14829.8755656109 3212.6696832579 0.0))
((0 . "LINE") (100 . "AcDbEntity") (8 . "LOUVERS") (62 . 7) (370 . 13) (100 . "AcDbLine") (10 14829.8755656109
3212.6696832579 0.0) (11 14864.8303167421 3212.6696832579 0.0))
((0 . "LINE") (100 . "AcDbEntity") (8 . "LOUVERS") (62 . 7) (370 . 13) (100 . "AcDbLine") (10 14864.8303167421
3212.6696832579 0.0) (11 14935.5090497738 3212.6696832579 0.0))
((0 . "LINE") (100 . "AcDbEntity") (8 . "LOUVERS") (62 . 7) (370 . 13) (100 . "AcDbLine") (10 14935.5090497738
3212.6696832579 0.0) (11 14997.9751131222 3212.6696832579 0.0))
((0 . "LINE") (100 . "AcDbEntity") (8 . "LOUVERS") (62 . 7) (370 . 13) (100 . "AcDbLine") (10 14997.9751131222
3212.6696832579 0.0) (11 15031.9004524887 3212.6696832579 0.0))
((0 . "LINE") (100 . "AcDbEntity") (8 . "LOUVERS") (62 . 7) (370 . 13) (100 . "AcDbLine") (10 15031.9004524887
3212.6696832579 0.0) (11 15067.2963800905 3212.6696832579 0.0))
((0 . "LINE") (100 . "AcDbEntity") (8 . "LOUVERS") (62 . 7) (370 . 13) (100 . "AcDbLine") (10 15067.2963800905
3212.6696832579 0.0) (11 15102.6244343891 3212.6696832579 0.0))
((0 . "LINE") (100 . "AcDbEntity") (8 . "LOUVERS") (62 . 7) (370 . 13) (100 . "AcDbLine") (10 15102.6244343891
3212.6696832579 0.0) (11 15143.0995475113 3212.6696832579 0.0))
((0 . "LINE") (100 . "AcDbEntity") (8 . "LOUVERS") (62 . 7) (370 . 13) (100 . "AcDbLine") (10 15143.0995475113
3212.6696832579 0.0) (11 15178.778280543 3212.6696832579 0.0))
((0 . "LINE") (100 . "AcDbEntity") (8 . "LOUVERS") (62 . 7) (370 . 13) (100 . "AcDbLine") (10 15178.778280543
3212.6696832579 0.0) (11 15215.8257918552 3212.6696832579 0.0))
((0 . "LINE") (100 . "AcDbEntity") (8 . "LOUVERS") (62 . 7) (370 . 13) (100 . "AcDbLine") (10 15215.8257918552
3212.6696832579 0.0) (11 15251.1085972851 3212.6696832579 0.0))
((0 . "LINE") (100 . "AcDbEntity") (8 . "LOUVERS") (62 . 7) (370 . 13) (100 . "AcDbLine") (10 15251.1085972851
3212.6696832579 0.0) (11 15287.8280542986 3212.6696832579 0.0))
((0 . "LINE") (100 . "AcDbEntity") (8 . "LOUVERS") (62 . 7) (370 . 13) (100 . "AcDbLine") (10 15287.8280542986
3212.6696832579 0.0) (11 15325.3846153846 3212.6696832579 0.0))
((0 . "LINE") (100 . "AcDbEntity") (8 . "LOUVERS") (62 . 7) (370 . 13) (100 . "AcDbLine") (10 15325.3846153846
3212.6696832579 0.0) (11 15360.9841628959 3212.6696832579 0.0))
((0 . "LINE") (100 . "AcDbEntity") (8 . "LOUVERS") (62 . 7) (370 . 13) (100 . "AcDbLine") (10 15360.9841628959
3212.6696832579 0.0) (11 15395.5429864253 3212.6696832579 0.0))
((0 . "LINE") (100 . "AcDbEntity") (8 . "LOUVERS") (62 . 7) (370 . 13) (100 . "AcDbLine") (10 15395.5429864253
3212.6696832579 0.0) (11 15430.7466063348 3212.6696832579 0.0))
((0 . "LINE") (100 . "AcDbEntity") (8 . "LOUVERS") (62 . 7) (370 . 13) (100 . "AcDbLine") (10 15430.7466063348
3212.6696832579 0.0) (11 15463.2352941176 3212.6696832579 0.0))
((0 . "LINE") (100 . "AcDbEntity") (8 . "LOUVERS") (62 . 7) (370 . 13) (100 . "AcDbLine") (10 15463.2352941176
3212.6696832579 0.0) (11 15509.4343891403 3212.6696832579 0.0))
((0 . "LINE") (100 . "AcDbEntity") (8 . "LOUVERS") (62 . 7) (370 . 13) (100 . "AcDbLine") (10 15509.4343891403
3212.6696832579 0.0) (11 15541.4819004525 3212.6696832579 0.0))
((0 . "LINE") (100 . "AcDbEntity") (8 . "LOUVERS") (62 . 7) (370 . 13) (100 . "AcDbLine") (10 15541.4819004525
3212.6696832579 0.0) (11 15579.1176470588 3212.6696832579 0.0))
((0 . "LINE") (100 . "AcDbEntity") (8 . "LOUVERS") (62 . 7) (370 . 13) (100 . "AcDbLine") (10 15579.1176470588
3212.6696832579 0.0) (11 15612.036199095 3212.6696832579 0.0))
((0 . "LINE") (100 . "AcDbEntity") (8 . "LOUVERS") (62 . 7) (370 . 13) (100 . "AcDbLine") (10 15612.036199095
3212.6696832579 0.0) (11 15644.6606334842 3212.6696832579 0.0))
((0 . "LINE") (100 . "AcDbEntity") (8 . "LOUVERS") (62 . 7) (370 . 13) (100 . "AcDbLine") (10 15644.6606334842
3212.6696832579 0.0) (11 15681.0180995475 3212.6696832579 0.0))
((0 . "LINE") (100 . "AcDbEntity") (8 . "LOUVERS") (62 . 7) (370 . 13) (100 . "AcDbLine") (10 15681.0180995475
3212.6696832579 0.0) (11 15698.7895927602 3212.6696832579 0.0))
((0 . "LINE") (100 . "AcDbEntity") (8 . "LOUVERS") (62 . 7) (370 . 13) (100 . "AcDbLine") (10 15698.7895927602
3212.6696832579 0.0) (11 15738.0542986425 3212.6696832579 0.0))
((0 . "LINE") (100 . "AcDbEntity") (8 . "LOUVERS") (62 . 7) (370 . 13) (100 . "AcDbLine") (10 15738.0542986425
3212.6696832579 0.0) (11 15756.8552036199 3212.6696832579 0.0))
((0 . "LINE") (100 . "AcDbEntity") (8 . "LOUVERS") (62 . 7) (370 . 13) (100 . "AcDbLine") (10 15756.8552036199
3212.6696832579 0.0) (11 15802.963800905 3212.6696832579 0.0))
((0 . "LINE") (100 . "AcDbEntity") (8 . "LOUVERS") (62 . 7) (370 . 13) (100 . "AcDbLine") (10 15802.963800905
3212.6696832579 0.0) (11 15828.6312217195 3212.6696832579 0.0))
((0 . "LINE") (100 . "AcDbEntity") (8 . "LOUVERS") (62 . 7) (370 . 13) (100 . "AcDbLine") (10 15828.6312217195
3212.6696832579 0.0) (11 15872.0814479638 3212.6696832579 0.0))
((0 . "LINE") (100 . "AcDbEntity") (8 . "LOUVERS") (62 . 7) (370 . 13) (100 . "AcDbLine") (10 15872.0814479638
3212.6696832579 0.0) (11 15901.0633484163 3212.6696832579 0.0))
((0 . "LINE") (100 . "AcDbEntity") (8 . "LOUVERS") (62 . 7) (370 . 13) (100 . "AcDbLine") (10 15901.0633484163
3212.6696832579 0.0) (11 15916.2895927602 3212.6696832579 0.0))
((0 . "LINE") (100 . "AcDbEntity") (8 . "LOUVERS") (62 . 7) (370 . 13) (100 . "AcDbLine") (10 15916.2895927602
3212.6696832579 0.0) (11 15916.2895927602 2952.4886877828 0.0))
((0 . "LINE") (100 . "AcDbEntity") (8 . "LOUVERS") (62 . 7) (370 . 13) (100 . "AcDbLine") (10 15916.2895927602
2952.4886877828 0.0) (11 15901.0633484163 2952.4886877828 0.0))
((0 . "LINE") (100 . "AcDbEntity") (8 . "LOUVERS") (62 . 7) (370 . 13) (100 . "AcDbLine") (10 15901.0633484163
2952.4886877828 0.0) (11 15872.0814479638 2952.4886877828 0.0))
((0 . "LINE") (100 . "AcDbEntity") (8 . "LOUVERS") (62 . 7) (370 . 13) (100 . "AcDbLine") (10 15872.0814479638
2952.4886877828 0.0) (11 15828.6312217195 2952.4886877828 0.0))
((0 . "LINE") (100 . "AcDbEntity") (8 . "LOUVERS") (62 . 7) (370 . 13) (100 . "AcDbLine") (10 15828.6312217195
2952.4886877828 0.0) (11 15802.963800905 2952.4886877828 0.0))
((0 . "LINE") (100 . "AcDbEntity") (8 . "LOUVERS") (62 . 7) (370 . 13) (100 . "AcDbLine") (10 15802.963800905
2952.4886877828 0.0) (11 15756.8552036199 2952.4886877828 0.0))
((0 . "LINE") (100 . "AcDbEntity") (8 . "LOUVERS") (62 . 7) (370 . 13) (100 . "AcDbLine") (10 15756.8552036199
2952.4886877828 0.0) (11 15738.0542986425 2952.4886877828 0.0))
((0 . "LINE") (100 . "AcDbEntity") (8 . "LOUVERS") (62 . 7) (370 . 13) (100 . "AcDbLine") (10 15738.0542986425
2952.4886877828 0.0) (11 15698.7895927602 2952.4886877828 0.0))
((0 . "LINE") (100 . "AcDbEntity") (8 . "LOUVERS") (62 . 7) (370 . 13) (100 . "AcDbLine") (10 15698.7895927602
2952.4886877828 0.0) (11 15681.0180995475 2952.4886877828 0.0))
((0 . "LINE") (100 . "AcDbEntity") (8 . "LOUVERS") (62 . 7) (370 . 13) (100 . "AcDbLine") (10 15681.0180995475
2952.4886877828 0.0) (11 15644.6606334842 2952.4886877828 0.0))
((0 . "LINE") (100 . "AcDbEntity") (8 . "LOUVERS") (62 . 7) (370 . 13) (100 . "AcDbLine") (10 15644.6606334842
2952.4886877828 0.0) (11 15612.036199095 2952.4886877828 0.0))
((0 . "LINE") (100 . "AcDbEntity") (8 . "LOUVERS") (62 . 7) (370 . 13) (100 . "AcDbLine") (10 15612.036199095
2952.4886877828 0.0) (11 15579.1176470588 2952.4886877828 0.0))
((0 . "LINE") (100 . "AcDbEntity") (8 . "LOUVERS") (62 . 7) (370 . 13) (100 . "AcDbLine") (10 15579.1176470588
2952.4886877828 0.0) (11 15541.4819004525 2952.4886877828 0.0))
((0 . "LINE") (100 . "AcDbEntity") (8 . "LOUVERS") (62 . 7) (370 . 13) (100 . "AcDbLine") (10 15541.4819004525
2952.4886877828 0.0) (11 15509.4343891403 2952.4886877828 0.0))
((0 . "LINE") (100 . "AcDbEntity") (8 . "LOUVERS") (62 . 7) (370 . 13) (100 . "AcDbLine") (10 15509.4343891403
2952.4886877828 0.0) (11 15463.2352941176 2952.4886877828 0.0))
((0 . "LINE") (100 . "AcDbEntity") (8 . "LOUVERS") (62 . 7) (370 . 13) (100 . "AcDbLine") (10 15463.2352941176
2952.4886877828 0.0) (11 15430.7466063348 2952.4886877828 0.0))
((0 . "LINE") (100 . "AcDbEntity") (8 . "LOUVERS") (62 . 7) (370 . 13) (100 . "AcDbLine") (10 15430.7466063348
2952.4886877828 0.0) (11 15395.5429864253 2952.4886877828 0.0))
((0 . "LINE") (100 . "AcDbEntity") (8 . "LOUVERS") (62 . 7) (370 . 13) (100 . "AcDbLine") (10 15395.5429864253
2952.4886877828 0.0) (11 15360.9841628959 2952.4886877828 0.0))
((0 . "LINE") (100 . "AcDbEntity") (8 . "LOUVERS") (62 . 7) (370 . 13) (100 . "AcDbLine") (10 15360.9841628959
2952.4886877828 0.0) (11 15325.3846153846 2952.4886877828 0.0))
((0 . "LINE") (100 . "AcDbEntity") (8 . "LOUVERS") (62 . 7) (370 . 13) (100 . "AcDbLine") (10 15325.3846153846
2952.4886877828 0.0) (11 15287.8280542986 2952.4886877828 0.0))
((0 . "LINE") (100 . "AcDbEntity") (8 . "LOUVERS") (62 . 7) (370 . 13) (100 . "AcDbLine") (10 15287.8280542986
2952.4886877828 0.0) (11 15251.1085972851 2952.4886877828 0.0))
((0 . "LINE") (100 . "AcDbEntity") (8 . "LOUVERS") (62 . 7) (370 . 13) (100 . "AcDbLine") (10 15251.1085972851
2952.4886877828 0.0) (11 15215.8257918552 2952.4886877828 0.0))
((0 . "LINE") (100 . "AcDbEntity") (8 . "LOUVERS") (62 . 7) (370 . 13) (100 . "AcDbLine") (10 15215.8257918552
2952.4886877828 0.0) (11 15178.778280543 2952.4886877828 0.0))
((0 . "LINE") (100 . "AcDbEntity") (8 . "LOUVERS") (62 . 7) (370 . 13) (100 . "AcDbLine") (10 15178.778280543
2952.4886877828 0.0) (11 15143.0995475113 2952.4886877828 0.0))
((0 . "LINE") (100 . "AcDbEntity") (8 . "LOUVERS") (62 . 7) (370 . 13) (100 . "AcDbLine") (10 15143.0995475113
2952.4886877828 0.0) (11 15102.6244343891 2952.4886877828 0.0))
((0 . "LINE") (100 . "AcDbEntity") (8 . "LOUVERS") (62 . 7) (370 . 13) (100 . "AcDbLine") (10 15102.6244343891
2952.4886877828 0.0) (11 15067.2963800905 2952.4886877828 0.0))
((0 . "LINE") (100 . "AcDbEntity") (8 . "LOUVERS") (62 . 7) (370 . 13) (100 . "AcDbLine") (10 15067.2963800905
2952.4886877828 0.0) (11 15031.9004524887 2952.4886877828 0.0))
((0 . "LINE") (100 . "AcDbEntity") (8 . "LOUVERS") (62 . 7) (370 . 13) (100 . "AcDbLine") (10 15031.9004524887
2952.4886877828 0.0) (11 14997.9751131222 2952.4886877828 0.0))
((0 . "LINE") (100 . "AcDbEntity") (8 . "LOUVERS") (62 . 7) (370 . 13) (100 . "AcDbLine") (10 14997.9751131222
2952.4886877828 0.0) (11 14935.5090497738 2952.4886877828 0.0))
((0 . "LINE") (100 . "AcDbEntity") (8 . "LOUVERS") (62 . 7) (370 . 13) (100 . "AcDbLine") (10 14935.5090497738
2952.4886877828 0.0) (11 14864.8303167421 2952.4886877828 0.0))
((0 . "LINE") (100 . "AcDbEntity") (8 . "LOUVERS") (62 . 7) (370 . 13) (100 . "AcDbLine") (10 14864.8303167421
2952.4886877828 0.0) (11 14829.8755656109 2952.4886877828 0.0))
((0 . "LINE") (100 . "AcDbEntity") (8 . "LOUVERS") (62 . 7) (370 . 13) (100 . "AcDbLine") (10 14829.8755656109
2952.4886877828 0.0) (11 14802.0475113122 2952.4886877828 0.0))
((0 . "LINE") (100 . "AcDbEntity") (8 . "LOUVERS") (62 . 7) (370 . 13) (100 . "AcDbLine") (10 14802.0475113122
2952.4886877828 0.0) (11 14774.5475113122 2952.4886877828 0.0))
((0 . "LINE") (100 . "AcDbEntity") (8 . "LOUVERS") (62 . 7) (370 . 13) (100 . "AcDbLine") (10 14774.5475113122
2952.4886877828 0.0) (11 14734.3552036199 2952.4886877828 0.0))
((0 . "LINE") (100 . "AcDbEntity") (8 . "LOUVERS") (62 . 7) (370 . 13) (100 . "AcDbLine") (10 14734.3552036199
2952.4886877828 0.0) (11 14687.5113122172 2952.4886877828 0.0))
((0 . "LINE") (100 . "AcDbEntity") (8 . "LOUVERS") (62 . 7) (370 . 13) (100 . "AcDbLine") (10 14687.5113122172
2952.4886877828 0.0) (11 14658.3936651584 2952.4886877828 0.0))
((0 . "LINE") (100 . "AcDbEntity") (8 . "LOUVERS") (62 . 7) (370 . 13) (100 . "AcDbLine") (10 14658.3936651584
2952.4886877828 0.0) (11 14622.3416289593 2952.4886877828 0.0))
((0 . "LINE") (100 . "AcDbEntity") (8 . "LOUVERS") (62 . 7) (370 . 13) (100 . "AcDbLine") (10 14622.3416289593
2952.4886877828 0.0) (11 14608.0316742081 2952.4886877828 0.0))
((0 . "LINE") (100 . "AcDbEntity") (8 . "LOUVERS") (62 . 7) (370 . 13) (100 . "AcDbLine") (10 14608.0316742081
2952.4886877828 0.0) (11 14569.1742081448 2952.4886877828 0.0))
((0 . "LINE") (100 . "AcDbEntity") (8 . "LOUVERS") (62 . 7) (370 . 13) (100 . "AcDbLine") (10 14569.1742081448
2952.4886877828 0.0) (11 14522.2058823529 2952.4886877828 0.0))
((0 . "LINE") (100 . "AcDbEntity") (8 . "LOUVERS") (62 . 7) (370 . 13) (100 . "AcDbLine") (10 14522.2058823529
2952.4886877828 0.0) (11 14506.2443438914 2952.4886877828 0.0))
((0 . "LINE") (100 . "AcDbEntity") (8 . "LOUVERS") (62 . 7) (370 . 13) (100 . "AcDbLine") (10 14506.2443438914
2952.4886877828 0.0) (11 14466.5045248869 2952.4886877828 0.0))
((0 . "LINE") (100 . "AcDbEntity") (8 . "LOUVERS") (62 . 7) (370 . 13) (100 . "AcDbLine") (10 14466.5045248869
2952.4886877828 0.0) (11 14446.9343891403 2952.4886877828 0.0))
((0 . "LINE") (100 . "AcDbEntity") (8 . "LOUVERS") (62 . 7) (370 . 13) (100 . "AcDbLine") (10 14446.9343891403
2952.4886877828 0.0) (11 14408.2239819005 2952.4886877828 0.0))
((0 . "LINE") (100 . "AcDbEntity") (8 . "LOUVERS") (62 . 7) (370 . 13) (100 . "AcDbLine") (10 14408.2239819005
2952.4886877828 0.0) (11 14391.4366515837 2952.4886877828 0.0))
((0 . "LINE") (100 . "AcDbEntity") (8 . "LOUVERS") (62 . 7) (370 . 13) (100 . "AcDbLine") (10 14391.4366515837
2952.4886877828 0.0) (11 14347.5904977376 2952.4886877828 0.0))
((0 . "LINE") (100 . "AcDbEntity") (8 . "LOUVERS") (62 . 7) (370 . 13) (100 . "AcDbLine") (10 14347.5904977376
2952.4886877828 0.0) (11 14308.834841629 2952.4886877828 0.0))
((0 . "LINE") (100 . "AcDbEntity") (8 . "LOUVERS") (62 . 7) (370 . 13) (100 . "AcDbLine") (10 14308.834841629
2952.4886877828 0.0) (11 14279.1742081448 2952.4886877828 0.0))
((0 . "LINE") (100 . "AcDbEntity") (8 . "LOUVERS") (62 . 7) (370 . 13) (100 . "AcDbLine") (10 14279.1742081448
2952.4886877828 0.0) (11 14231.8552036199 2952.4886877828 0.0))
((0 . "LINE") (100 . "AcDbEntity") (8 . "LOUVERS") (62 . 7) (370 . 13) (100 . "AcDbLine") (10 14231.8552036199
2952.4886877828 0.0) (11 14209.5248868778 2952.4886877828 0.0))
((0 . "LINE") (100 . "AcDbEntity") (8 . "LOUVERS") (62 . 7) (370 . 13) (100 . "AcDbLine") (10 14209.5248868778
2952.4886877828 0.0) (11 14171.6968325792 2952.4886877828 0.0))
((0 . "LINE") (100 . "AcDbEntity") (8 . "LOUVERS") (62 . 7) (370 . 13) (100 . "AcDbLine") (10 14171.6968325792
2952.4886877828 0.0) (11 14142.7036199095 2952.4886877828 0.0))
((0 . "LINE") (100 . "AcDbEntity") (8 . "LOUVERS") (62 . 7) (370 . 13) (100 . "AcDbLine") (10 14142.7036199095
2952.4886877828 0.0) (11 14109.8190045249 2952.4886877828 0.0))
((0 . "LINE") (100 . "AcDbEntity") (8 . "LOUVERS") (62 . 7) (370 . 13) (100 . "AcDbLine") (10 14109.8190045249
2952.4886877828 0.0) (11 14082.8846153846 2952.4886877828 0.0))
((0 . "LINE") (100 . "AcDbEntity") (8 . "LOUVERS") (62 . 7) (370 . 13) (100 . "AcDbLine") (10 14082.8846153846
2952.4886877828 0.0) (11 14027.9298642534 2952.4886877828 0.0))
((0 . "LINE") (100 . "AcDbEntity") (8 . "LOUVERS") (62 . 7) (370 . 13) (100 . "AcDbLine") (10 14027.9298642534
2952.4886877828 0.0) (11 13991.7081447964 2952.4886877828 0.0))
((0 . "LINE") (100 . "AcDbEntity") (8 . "LOUVERS") (62 . 7) (370 . 13) (100 . "AcDbLine") (10 13991.7081447964
2952.4886877828 0.0) (11 13954.7850678733 2952.4886877828 0.0))
((0 . "LINE") (100 . "AcDbEntity") (8 . "LOUVERS") (62 . 7) (370 . 13) (100 . "AcDbLine") (10 13954.7850678733
2952.4886877828 0.0) (11 13923.5520361991 2952.4886877828 0.0))
((0 . "LINE") (100 . "AcDbEntity") (8 . "LOUVERS") (62 . 7) (370 . 13) (100 . "AcDbLine") (10 13923.5520361991
2952.4886877828 0.0) (11 13887.5791855204 2952.4886877828 0.0))
((0 . "LINE") (100 . "AcDbEntity") (8 . "LOUVERS") (62 . 7) (370 . 13) (100 . "AcDbLine") (10 13887.5791855204
2952.4886877828 0.0) (11 13857.6583710407 2952.4886877828 0.0))
((0 . "LINE") (100 . "AcDbEntity") (8 . "LOUVERS") (62 . 7) (370 . 13) (100 . "AcDbLine") (10 13857.6583710407
2952.4886877828 0.0) (11 13824.4796380091 2952.4886877828 0.0))
((0 . "LINE") (100 . "AcDbEntity") (8 . "LOUVERS") (62 . 7) (370 . 13) (100 . "AcDbLine") (10 13824.4796380091
2952.4886877828 0.0) (11 13791.9117647059 2952.4886877828 0.0))
((0 . "LINE") (100 . "AcDbEntity") (8 . "LOUVERS") (62 . 7) (370 . 13) (100 . "AcDbLine") (10 13791.9117647059
2952.4886877828 0.0) (11 13757.5113122172 2952.4886877828 0.0))
((0 . "LINE") (100 . "AcDbEntity") (8 . "LOUVERS") (62 . 7) (370 . 13) (100 . "AcDbLine") (10 13757.5113122172
2952.4886877828 0.0) (11 13722.0814479638 2952.4886877828 0.0))
((0 . "LINE") (100 . "AcDbEntity") (8 . "LOUVERS") (62 . 7) (370 . 13) (100 . "AcDbLine") (10 13722.0814479638
2952.4886877828 0.0) (11 13679.6832579186 2952.4886877828 0.0))
((0 . "LINE") (100 . "AcDbEntity") (8 . "LOUVERS") (62 . 7) (370 . 13) (100 . "AcDbLine") (10 13679.6832579186
2952.4886877828 0.0) (11 13641.4479638009 2952.4886877828 0.0))
((0 . "LINE") (100 . "AcDbEntity") (8 . "LOUVERS") (62 . 7) (370 . 13) (100 . "AcDbLine") (10 13641.4479638009
2952.4886877828 0.0) (11 13600.3959276018 2952.4886877828 0.0))
((0 . "LINE") (100 . "AcDbEntity") (8 . "LOUVERS") (62 . 7) (370 . 13) (100 . "AcDbLine") (10 13600.3959276018
2952.4886877828 0.0) (11 13570.4411764706 2952.4886877828 0.0))
((0 . "LINE") (100 . "AcDbEntity") (8 . "LOUVERS") (62 . 7) (370 . 13) (100 . "AcDbLine") (10 13570.4411764706
2952.4886877828 0.0) (11 13531.221719457 2952.4886877828 0.0))
((0 . "LINE") (100 . "AcDbEntity") (8 . "LOUVERS") (62 . 7) (370 . 13) (100 . "AcDbLine") (10 13531.221719457
2952.4886877828 0.0) (11 13498.2918552036 2952.4886877828 0.0))
((0 . "LINE") (100 . "AcDbEntity") (8 . "LOUVERS") (62 . 7) (370 . 13) (100 . "AcDbLine") (10 13498.2918552036
2952.4886877828 0.0) (11 13451.7307692308 2952.4886877828 0.0))
((0 . "LINE") (100 . "AcDbEntity") (8 . "LOUVERS") (62 . 7) (370 . 13) (100 . "AcDbLine") (10 13451.7307692308
2952.4886877828 0.0) (11 13416.2895927602 2952.4886877828 0.0))
((0 . "LINE") (100 . "AcDbEntity") (8 . "LOUVERS") (62 . 7) (370 . 13) (100 . "AcDbLine") (10 13416.2895927602
2952.4886877828 0.0) (11 13379.1628959276 2952.4886877828 0.0))
((0 . "LINE") (100 . "AcDbEntity") (8 . "LOUVERS") (62 . 7) (370 . 13) (100 . "AcDbLine") (10 13379.1628959276
2952.4886877828 0.0) (11 13333.257918552 2952.4886877828 0.0))
((0 . "LINE") (100 . "AcDbEntity") (8 . "LOUVERS") (62 . 7) (370 . 13) (100 . "AcDbLine") (10 13333.257918552
2952.4886877828 0.0) (11 13296.2895927602 2952.4886877828 0.0))
((0 . "LINE") (100 . "AcDbEntity") (8 . "LOUVERS") (62 . 7) (370 . 13) (100 . "AcDbLine") (10 13296.2895927602
2952.4886877828 0.0) (11 13246.8778280543 2952.4886877828 0.0))
((0 . "LINE") (100 . "AcDbEntity") (8 . "LOUVERS") (62 . 7) (370 . 13) (100 . "AcDbLine") (10 13246.8778280543
2952.4886877828 0.0) (11 13212.6696832579 2952.4886877828 0.0))
((0 . "LINE") (100 . "AcDbEntity") (8 . "LOUVERS") (62 . 7) (370 . 13) (100 . "AcDbLine") (10 13212.6696832579
2952.4886877828 0.0) (11 13212.6696832579 3212.6696832579 0.0))
((0 . "LINE") (100 . "AcDbEntity") (8 . "LOUVERS") (62 . 7) (370 . 13) (100 . "AcDbLine") (10 13246.8778280543
3212.6696832579 0.0) (11 13246.8778280543 2952.4886877828 0.0))
((0 . "LINE") (100 . "AcDbEntity") (8 . "LOUVERS") (62 . 7) (370 . 13) (100 . "AcDbLine") (10 13296.2895927602
3212.6696832579 0.0) (11 13296.2895927602 2952.4886877828 0.0))
((0 . "LINE") (100 . "AcDbEntity") (8 . "LOUVERS") (62 . 7) (370 . 13) (100 . "AcDbLine") (10 13333.257918552
3212.6696832579 0.0) (11 13333.257918552 2952.4886877828 0.0))
((0 . "LINE") (100 . "AcDbEntity") (8 . "LOUVERS") (62 . 7) (370 . 13) (100 . "AcDbLine") (10 13379.1628959276
3212.6696832579 0.0) (11 13379.1628959276 2952.4886877828 0.0))
((0 . "LINE") (100 . "AcDbEntity") (8 . "LOUVERS") (62 . 7) (370 . 13) (100 . "AcDbLine") (10 13416.2895927602
3212.6696832579 0.0) (11 13416.2895927602 2952.4886877828 0.0))
((0 . "LINE") (100 . "AcDbEntity") (8 . "LOUVERS") (62 . 7) (370 . 13) (100 . "AcDbLine") (10 13451.7307692308
3212.6696832579 0.0) (11 13451.7307692308 2952.4886877828 0.0))
((0 . "LINE") (100 . "AcDbEntity") (8 . "LOUVERS") (62 . 7) (370 . 13) (100 . "AcDbLine") (10 13498.2918552036
3212.6696832579 0.0) (11 13498.2918552036 2952.4886877828 0.0))
((0 . "LINE") (100 . "AcDbEntity") (8 . "LOUVERS") (62 . 7) (370 . 13) (100 . "AcDbLine") (10 13531.221719457
3212.6696832579 0.0) (11 13531.221719457 2952.4886877828 0.0))
((0 . "LINE") (100 . "AcDbEntity") (8 . "LOUVERS") (62 . 7) (370 . 13) (100 . "AcDbLine") (10 13570.4411764706
3212.6696832579 0.0) (11 13570.4411764706 2952.4886877828 0.0))
((0 . "LINE") (100 . "AcDbEntity") (8 . "LOUVERS") (62 . 7) (370 . 13) (100 . "AcDbLine") (10 13600.3959276018
3212.6696832579 0.0) (11 13600.3959276018 2952.4886877828 0.0))
((0 . "LINE") (100 . "AcDbEntity") (8 . "LOUVERS") (62 . 7) (370 . 13) (100 . "AcDbLine") (10 13641.4479638009
3212.6696832579 0.0) (11 13641.4479638009 2952.4886877828 0.0))
((0 . "LINE") (100 . "AcDbEntity") (8 . "LOUVERS") (62 . 7) (370 . 13) (100 . "AcDbLine") (10 13679.6832579186
3212.6696832579 0.0) (11 13679.6832579186 2952.4886877828 0.0))
((0 . "LINE") (100 . "AcDbEntity") (8 . "LOUVERS") (62 . 7) (370 . 13) (100 . "AcDbLine") (10 13722.0814479638
3212.6696832579 0.0) (11 13722.0814479638 2952.4886877828 0.0))
((0 . "LINE") (100 . "AcDbEntity") (8 . "LOUVERS") (62 . 7) (370 . 13) (100 . "AcDbLine") (10 13757.5113122172
3212.6696832579 0.0) (11 13757.5113122172 2952.4886877828 0.0))
((0 . "LINE") (100 . "AcDbEntity") (8 . "LOUVERS") (62 . 7) (370 . 13) (100 . "AcDbLine") (10 13791.9117647059
3212.6696832579 0.0) (11 13791.9117647059 2952.4886877828 0.0))
((0 . "LINE") (100 . "AcDbEntity") (8 . "LOUVERS") (62 . 7) (370 . 13) (100 . "AcDbLine") (10 13824.4796380091
3212.6696832579 0.0) (11 13824.4796380091 2952.4886877828 0.0))
((0 . "LINE") (100 . "AcDbEntity") (8 . "LOUVERS") (62 . 7) (370 . 13) (100 . "AcDbLine") (10 13857.6583710407
3212.6696832579 0.0) (11 13857.6583710407 2952.4886877828 0.0))
((0 . "LINE") (100 . "AcDbEntity") (8 . "LOUVERS") (62 . 7) (370 . 13) (100 . "AcDbLine") (10 13887.5791855204
3212.6696832579 0.0) (11 13887.5791855204 2952.4886877828 0.0))
((0 . "LINE") (100 . "AcDbEntity") (8 . "LOUVERS") (62 . 7) (370 . 13) (100 . "AcDbLine") (10 13923.5520361991
3212.6696832579 0.0) (11 13923.5520361991 2952.4886877828 0.0))
((0 . "LINE") (100 . "AcDbEntity") (8 . "LOUVERS") (62 . 7) (370 . 13) (100 . "AcDbLine") (10 13954.7850678733
3212.6696832579 0.0) (11 13954.7850678733 2952.4886877828 0.0))
((0 . "LINE") (100 . "AcDbEntity") (8 . "LOUVERS") (62 . 7) (370 . 13) (100 . "AcDbLine") (10 13991.7081447964
3212.6696832579 0.0) (11 13991.7081447964 2952.4886877828 0.0))
((0 . "LINE") (100 . "AcDbEntity") (8 . "LOUVERS") (62 . 7) (370 . 13) (100 . "AcDbLine") (10 14027.9298642534
3212.6696832579 0.0) (11 14027.9298642534 2952.4886877828 0.0))
((0 . "LINE") (100 . "AcDbEntity") (8 . "LOUVERS") (62 . 7) (370 . 13) (100 . "AcDbLine") (10 14082.8846153846
3212.6696832579 0.0) (11 14082.8846153846 2952.4886877828 0.0))
((0 . "LINE") (100 . "AcDbEntity") (8 . "LOUVERS") (62 . 7) (370 . 13) (100 . "AcDbLine") (10 14109.8190045249
3212.6696832579 0.0) (11 14109.8190045249 2952.4886877828 0.0))
((0 . "LINE") (100 . "AcDbEntity") (8 . "LOUVERS") (62 . 7) (370 . 13) (100 . "AcDbLine") (10 14142.7036199095
3212.6696832579 0.0) (11 14142.7036199095 2952.4886877828 0.0))
((0 . "LINE") (100 . "AcDbEntity") (8 . "LOUVERS") (62 . 7) (370 . 13) (100 . "AcDbLine") (10 14171.6968325792
3212.6696832579 0.0) (11 14171.6968325792 2952.4886877828 0.0))
((0 . "LINE") (100 . "AcDbEntity") (8 . "LOUVERS") (62 . 7) (370 . 13) (100 . "AcDbLine") (10 14209.5248868778
3212.6696832579 0.0) (11 14209.5248868778 2952.4886877828 0.0))
((0 . "LINE") (100 . "AcDbEntity") (8 . "LOUVERS") (62 . 7) (370 . 13) (100 . "AcDbLine") (10 14231.8552036199
3212.6696832579 0.0) (11 14231.8552036199 2952.4886877828 0.0))
((0 . "LINE") (100 . "AcDbEntity") (8 . "LOUVERS") (62 . 7) (370 . 13) (100 . "AcDbLine") (10 14279.1742081448
3212.6696832579 0.0) (11 14279.1742081448 2952.4886877828 0.0))
((0 . "LINE") (100 . "AcDbEntity") (8 . "LOUVERS") (62 . 7) (370 . 13) (100 . "AcDbLine") (10 14308.834841629
3212.6696832579 0.0) (11 14308.834841629 2952.4886877828 0.0))
((0 . "LINE") (100 . "AcDbEntity") (8 . "LOUVERS") (62 . 7) (370 . 13) (100 . "AcDbLine") (10 14347.5904977376
3212.6696832579 0.0) (11 14347.5904977376 2952.4886877828 0.0))
((0 . "LINE") (100 . "AcDbEntity") (8 . "LOUVERS") (62 . 7) (370 . 13) (100 . "AcDbLine") (10 14391.4366515837
3212.6696832579 0.0) (11 14391.4366515837 2952.4886877828 0.0))
((0 . "LINE") (100 . "AcDbEntity") (8 . "LOUVERS") (62 . 7) (370 . 13) (100 . "AcDbLine") (10 14408.2239819005
3212.6696832579 0.0) (11 14408.2239819005 2952.4886877828 0.0))
((0 . "LINE") (100 . "AcDbEntity") (8 . "LOUVERS") (62 . 7) (370 . 13) (100 . "AcDbLine") (10 14446.9343891403
3212.6696832579 0.0) (11 14446.9343891403 2952.4886877828 0.0))
((0 . "LINE") (100 . "AcDbEntity") (8 . "LOUVERS") (62 . 7) (370 . 13) (100 . "AcDbLine") (10 14466.5045248869
3212.6696832579 0.0) (11 14466.5045248869 2952.4886877828 0.0))
((0 . "LINE") (100 . "AcDbEntity") (8 . "LOUVERS") (62 . 7) (370 . 13) (100 . "AcDbLine") (10 14506.2443438914
3212.6696832579 0.0) (11 14506.2443438914 2952.4886877828 0.0))
((0 . "LINE") (100 . "AcDbEntity") (8 . "LOUVERS") (62 . 7) (370 . 13) (100 . "AcDbLine") (10 14522.2058823529
3212.6696832579 0.0) (11 14522.2058823529 2952.4886877828 0.0))
((0 . "LINE") (100 . "AcDbEntity") (8 . "LOUVERS") (62 . 7) (370 . 13) (100 . "AcDbLine") (10 14569.1742081448
3212.6696832579 0.0) (11 14569.1742081448 2952.4886877828 0.0))
((0 . "LINE") (100 . "AcDbEntity") (8 . "LOUVERS") (62 . 7) (370 . 13) (100 . "AcDbLine") (10 14608.0316742081
3212.6696832579 0.0) (11 14608.0316742081 2952.4886877828 0.0))
((0 . "LINE") (100 . "AcDbEntity") (8 . "LOUVERS") (62 . 7) (370 . 13) (100 . "AcDbLine") (10 14622.3416289593
3212.6696832579 0.0) (11 14622.3416289593 2952.4886877828 0.0))
((0 . "LINE") (100 . "AcDbEntity") (8 . "LOUVERS") (62 . 7) (370 . 13) (100 . "AcDbLine") (10 14658.3936651584
3212.6696832579 0.0) (11 14658.3936651584 2952.4886877828 0.0))
((0 . "LINE") (100 . "AcDbEntity") (8 . "LOUVERS") (62 . 7) (370 . 13) (100 . "AcDbLine") (10 14687.5113122172
3212.6696832579 0.0) (11 14687.5113122172 2952.4886877828 0.0))
((0 . "LINE") (100 . "AcDbEntity") (8 . "LOUVERS") (62 . 7) (370 . 13) (100 . "AcDbLine") (10 14734.3552036199
3212.6696832579 0.0) (11 14734.3552036199 2952.4886877828 0.0))
((0 . "LINE") (100 . "AcDbEntity") (8 . "LOUVERS") (62 . 7) (370 . 13) (100 . "AcDbLine") (10 14774.5475113122
3212.6696832579 0.0) (11 14774.5475113122 2952.4886877828 0.0))
((0 . "LINE") (100 . "AcDbEntity") (8 . "LOUVERS") (62 . 7) (370 . 13) (100 . "AcDbLine") (10 14802.0475113122
3212.6696832579 0.0) (11 14802.0475113122 2952.4886877828 0.0))
((0 . "LINE") (100 . "AcDbEntity") (8 . "LOUVERS") (62 . 7) (370 . 13) (100 . "AcDbLine") (10 14829.8755656109
3212.6696832579 0.0) (11 14829.8755656109 2952.4886877828 0.0))
((0 . "LINE") (100 . "AcDbEntity") (8 . "LOUVERS") (62 . 7) (370 . 13) (100 . "AcDbLine") (10 14864.8303167421
3212.6696832579 0.0) (11 14864.8303167421 2952.4886877828 0.0))
((0 . "LINE") (100 . "AcDbEntity") (8 . "LOUVERS") (62 . 7) (370 . 13) (100 . "AcDbLine") (10 14935.5090497738
3212.6696832579 0.0) (11 14935.5090497738 2952.4886877828 0.0))
((0 . "LINE") (100 . "AcDbEntity") (8 . "LOUVERS") (62 . 7) (370 . 13) (100 . "AcDbLine") (10 14997.9751131222
3212.6696832579 0.0) (11 14997.9751131222 2952.4886877828 0.0))
((0 . "LINE") (100 . "AcDbEntity") (8 . "LOUVERS") (62 . 7) (370 . 13) (100 . "AcDbLine") (10 15031.9004524887
3212.6696832579 0.0) (11 15031.9004524887 2952.4886877828 0.0))
((0 . "LINE") (100 . "AcDbEntity") (8 . "LOUVERS") (62 . 7) (370 . 13) (100 . "AcDbLine") (10 15067.2963800905
3212.6696832579 0.0) (11 15067.2963800905 2952.4886877828 0.0))
((0 . "LINE") (100 . "AcDbEntity") (8 . "LOUVERS") (62 . 7) (370 . 13) (100 . "AcDbLine") (10 15102.6244343891
3212.6696832579 0.0) (11 15102.6244343891 2952.4886877828 0.0))
((0 . "LINE") (100 . "AcDbEntity") (8 . "LOUVERS") (62 . 7) (370 . 13) (100 . "AcDbLine") (10 15143.0995475113
3212.6696832579 0.0) (11 15143.0995475113 2952.4886877828 0.0))
((0 . "LINE") (100 . "AcDbEntity") (8 . "LOUVERS") (62 . 7) (370 . 13) (100 . "AcDbLine") (10 15178.778280543
3212.6696832579 0.0) (11 15178.778280543 2952.4886877828 0.0))
((0 . "LINE") (100 . "AcDbEntity") (8 . "LOUVERS") (62 . 7) (370 . 13) (100 . "AcDbLine") (10 15215.8257918552
3212.6696832579 0.0) (11 15215.8257918552 2952.4886877828 0.0))
((0 . "LINE") (100 . "AcDbEntity") (8 . "LOUVERS") (62 . 7) (370 . 13) (100 . "AcDbLine") (10 15251.1085972851
3212.6696832579 0.0) (11 15251.1085972851 2952.4886877828 0.0))
((0 . "LINE") (100 . "AcDbEntity") (8 . "LOUVERS") (62 . 7) (370 . 13) (100 . "AcDbLine") (10 15287.8280542986
3212.6696832579 0.0) (11 15287.8280542986 2952.4886877828 0.0))
((0 . "LINE") (100 . "AcDbEntity") (8 . "LOUVERS") (62 . 7) (370 . 13) (100 . "AcDbLine") (10 15325.3846153846
3212.6696832579 0.0) (11 15325.3846153846 2952.4886877828 0.0))
((0 . "LINE") (100 . "AcDbEntity") (8 . "LOUVERS") (62 . 7) (370 . 13) (100 . "AcDbLine") (10 15360.9841628959
3212.6696832579 0.0) (11 15360.9841628959 2952.4886877828 0.0))
((0 . "LINE") (100 . "AcDbEntity") (8 . "LOUVERS") (62 . 7) (370 . 13) (100 . "AcDbLine") (10 15395.5429864253
3212.6696832579 0.0) (11 15395.5429864253 2952.4886877828 0.0))
((0 . "LINE") (100 . "AcDbEntity") (8 . "LOUVERS") (62 . 7) (370 . 13) (100 . "AcDbLine") (10 15430.7466063348
3212.6696832579 0.0) (11 15430.7466063348 2952.4886877828 0.0))
((0 . "LINE") (100 . "AcDbEntity") (8 . "LOUVERS") (62 . 7) (370 . 13) (100 . "AcDbLine") (10 15463.2352941176
3212.6696832579 0.0) (11 15463.2352941176 2952.4886877828 0.0))
((0 . "LINE") (100 . "AcDbEntity") (8 . "LOUVERS") (62 . 7) (370 . 13) (100 . "AcDbLine") (10 15509.4343891403
3212.6696832579 0.0) (11 15509.4343891403 2952.4886877828 0.0))
((0 . "LINE") (100 . "AcDbEntity") (8 . "LOUVERS") (62 . 7) (370 . 13) (100 . "AcDbLine") (10 15541.4819004525
3212.6696832579 0.0) (11 15541.4819004525 2952.4886877828 0.0))
((0 . "LINE") (100 . "AcDbEntity") (8 . "LOUVERS") (62 . 7) (370 . 13) (100 . "AcDbLine") (10 15579.1176470588
3212.6696832579 0.0) (11 15579.1176470588 2952.4886877828 0.0))
((0 . "LINE") (100 . "AcDbEntity") (8 . "LOUVERS") (62 . 7) (370 . 13) (100 . "AcDbLine") (10 15612.036199095
3212.6696832579 0.0) (11 15612.036199095 2952.4886877828 0.0))
((0 . "LINE") (100 . "AcDbEntity") (8 . "LOUVERS") (62 . 7) (370 . 13) (100 . "AcDbLine") (10 15644.6606334842
3212.6696832579 0.0) (11 15644.6606334842 2952.4886877828 0.0))
((0 . "LINE") (100 . "AcDbEntity") (8 . "LOUVERS") (62 . 7) (370 . 13) (100 . "AcDbLine") (10 15681.0180995475
3212.6696832579 0.0) (11 15681.0180995475 2952.4886877828 0.0))
((0 . "LINE") (100 . "AcDbEntity") (8 . "LOUVERS") (62 . 7) (370 . 13) (100 . "AcDbLine") (10 15698.7895927602
3212.6696832579 0.0) (11 15698.7895927602 2952.4886877828 0.0))
((0 . "LINE") (100 . "AcDbEntity") (8 . "LOUVERS") (62 . 7) (370 . 13) (100 . "AcDbLine") (10 15738.0542986425
3212.6696832579 0.0) (11 15738.0542986425 2952.4886877828 0.0))
((0 . "LINE") (100 . "AcDbEntity") (8 . "LOUVERS") (62 . 7) (370 . 13) (100 . "AcDbLine") (10 15756.8552036199
3212.6696832579 0.0) (11 15756.8552036199 2952.4886877828 0.0))
((0 . "LINE") (100 . "AcDbEntity") (8 . "LOUVERS") (62 . 7) (370 . 13) (100 . "AcDbLine") (10 15802.963800905
3212.6696832579 0.0) (11 15802.963800905 2952.4886877828 0.0))
((0 . "LINE") (100 . "AcDbEntity") (8 . "LOUVERS") (62 . 7) (370 . 13) (100 . "AcDbLine") (10 15828.6312217195
3212.6696832579 0.0) (11 15828.6312217195 2952.4886877828 0.0))
((0 . "LINE") (100 . "AcDbEntity") (8 . "LOUVERS") (62 . 7) (370 . 13) (100 . "AcDbLine") (10 15872.0814479638
3212.6696832579 0.0) (11 15872.0814479638 2952.4886877828 0.0))
((0 . "LINE") (100 . "AcDbEntity") (8 . "LOUVERS") (62 . 7) (370 . 13) (100 . "AcDbLine") (10 15901.0633484163
3212.6696832579 0.0) (11 15901.0633484163 2952.4886877828 0.0))
((0 . "LINE") (100 . "AcDbEntity") (8 . "LOUVERS") (62 . 7) (370 . 13) (100 . "AcDbLine") (10 13506.7873303167
2194.5701357466 0.0) (11 13516.9230769231 2194.5701357466 0.0))
((0 . "LINE") (100 . "AcDbEntity") (8 . "LOUVERS") (62 . 7) (370 . 13) (100 . "AcDbLine") (10 13516.9230769231
2194.5701357466 0.0) (11 13551.4140271493 2194.5701357466 0.0))
((0 . "LINE") (100 . "AcDbEntity") (8 . "LOUVERS") (62 . 7) (370 . 13) (100 . "AcDbLine") (10 13551.4140271493
2194.5701357466 0.0) (11 13575.3054298643 2194.5701357466 0.0))
((0 . "LINE") (100 . "AcDbEntity") (8 . "LOUVERS") (62 . 7) (370 . 13) (100 . "AcDbLine") (10 13575.3054298643
2194.5701357466 0.0) (11 13608.4049773756 2194.5701357466 0.0))
((0 . "LINE") (100 . "AcDbEntity") (8 . "LOUVERS") (62 . 7) (370 . 13) (100 . "AcDbLine") (10 13608.4049773756
2194.5701357466 0.0) (11 13639.9773755656 2194.5701357466 0.0))
((0 . "LINE") (100 . "AcDbEntity") (8 . "LOUVERS") (62 . 7) (370 . 13) (100 . "AcDbLine") (10 13639.9773755656
2194.5701357466 0.0) (11 13674.2647058824 2194.5701357466 0.0))
((0 . "LINE") (100 . "AcDbEntity") (8 . "LOUVERS") (62 . 7) (370 . 13) (100 . "AcDbLine") (10 13674.2647058824
2194.5701357466 0.0) (11 13701.7081447964 2194.5701357466 0.0))
((0 . "LINE") (100 . "AcDbEntity") (8 . "LOUVERS") (62 . 7) (370 . 13) (100 . "AcDbLine") (10 13701.7081447964
2194.5701357466 0.0) (11 13731.2104072398 2194.5701357466 0.0))
((0 . "LINE") (100 . "AcDbEntity") (8 . "LOUVERS") (62 . 7) (370 . 13) (100 . "AcDbLine") (10 13731.2104072398
2194.5701357466 0.0) (11 13766.1990950226 2194.5701357466 0.0))
((0 . "LINE") (100 . "AcDbEntity") (8 . "LOUVERS") (62 . 7) (370 . 13) (100 . "AcDbLine") (10 13766.1990950226
2194.5701357466 0.0) (11 13812.2171945701 2194.5701357466 0.0))
((0 . "LINE") (100 . "AcDbEntity") (8 . "LOUVERS") (62 . 7) (370 . 13) (100 . "AcDbLine") (10 13812.2171945701
2194.5701357466 0.0) (11 13812.2171945701 2183.257918552 0.0))
((0 . "LINE") (100 . "AcDbEntity") (8 . "WINDOWS") (62 . 7) (370 . 13) (100 . "AcDbLine") (10 13812.2171945701
2183.257918552 0.0) (11 13812.2171945701 972.850678733 0.0))
((0 . "LINE") (100 . "AcDbEntity") (8 . "LOUVERS") (62 . 7) (370 . 13) (100 . "AcDbLine") (10 13812.2171945701
972.850678733 0.0) (11 13766.1990950226 972.850678733 0.0))
((0 . "LINE") (100 . "AcDbEntity") (8 . "LOUVERS") (62 . 7) (370 . 13) (100 . "AcDbLine") (10 13766.1990950226
972.850678733 0.0) (11 13731.2104072398 972.850678733 0.0))
((0 . "LINE") (100 . "AcDbEntity") (8 . "LOUVERS") (62 . 7) (370 . 13) (100 . "AcDbLine") (10 13731.2104072398
972.850678733 0.0) (11 13701.7081447964 972.850678733 0.0))
((0 . "LINE") (100 . "AcDbEntity") (8 . "LOUVERS") (62 . 7) (370 . 13) (100 . "AcDbLine") (10 13701.7081447964
972.850678733 0.0) (11 13674.2647058824 972.850678733 0.0))
((0 . "LINE") (100 . "AcDbEntity") (8 . "LOUVERS") (62 . 7) (370 . 13) (100 . "AcDbLine") (10 13674.2647058824
972.850678733 0.0) (11 13639.9773755656 972.850678733 0.0))
((0 . "LINE") (100 . "AcDbEntity") (8 . "LOUVERS") (62 . 7) (370 . 13) (100 . "AcDbLine") (10 13639.9773755656
972.850678733 0.0) (11 13608.4049773756 972.850678733 0.0))
((0 . "LINE") (100 . "AcDbEntity") (8 . "LOUVERS") (62 . 7) (370 . 13) (100 . "AcDbLine") (10 13608.4049773756
972.850678733 0.0) (11 13575.3054298643 972.850678733 0.0))
((0 . "LINE") (100 . "AcDbEntity") (8 . "LOUVERS") (62 . 7) (370 . 13) (100 . "AcDbLine") (10 13575.3054298643
972.850678733 0.0) (11 13551.4140271493 972.850678733 0.0))
((0 . "LINE") (100 . "AcDbEntity") (8 . "LOUVERS") (62 . 7) (370 . 13) (100 . "AcDbLine") (10 13551.4140271493
972.850678733 0.0) (11 13516.9230769231 972.850678733 0.0))
((0 . "LINE") (100 . "AcDbEntity") (8 . "LOUVERS") (62 . 7) (370 . 13) (100 . "AcDbLine") (10 13516.9230769231
972.850678733 0.0) (11 13506.7873303167 972.850678733 0.0))
((0 . "LINE") (100 . "AcDbEntity") (8 . "LOUVERS") (62 . 7) (370 . 13) (100 . "AcDbLine") (10 13506.7873303167
972.850678733 0.0) (11 13506.7873303167 2194.5701357466 0.0))
((0 . "LINE") (100 . "AcDbEntity") (8 . "LOUVERS") (62 . 7) (370 . 13) (100 . "AcDbLine") (10 13516.9230769231
2194.5701357466 0.0) (11 13516.9230769231 972.850678733 0.0))
((0 . "LINE") (100 . "AcDbEntity") (8 . "LOUVERS") (62 . 7) (370 . 13) (100 . "AcDbLine") (10 13551.4140271493
2194.5701357466 0.0) (11 13551.4140271493 972.850678733 0.0))
((0 . "LINE") (100 . "AcDbEntity") (8 . "LOUVERS") (62 . 7) (370 . 13) (100 . "AcDbLine") (10 13575.3054298643
2194.5701357466 0.0) (11 13575.3054298643 972.850678733 0.0))
((0 . "LINE") (100 . "AcDbEntity") (8 . "LOUVERS") (62 . 7) (370 . 13) (100 . "AcDbLine") (10 13608.4049773756
2194.5701357466 0.0) (11 13608.4049773756 972.850678733 0.0))
((0 . "LINE") (100 . "AcDbEntity") (8 . "LOUVERS") (62 . 7) (370 . 13) (100 . "AcDbLine") (10 13639.9773755656
2194.5701357466 0.0) (11 13639.9773755656 972.850678733 0.0))
((0 . "LINE") (100 . "AcDbEntity") (8 . "LOUVERS") (62 . 7) (370 . 13) (100 . "AcDbLine") (10 13674.2647058824
2194.5701357466 0.0) (11 13674.2647058824 972.850678733 0.0))
((0 . "LINE") (100 . "AcDbEntity") (8 . "LOUVERS") (62 . 7) (370 . 13) (100 . "AcDbLine") (10 13701.7081447964
2194.5701357466 0.0) (11 13701.7081447964 972.850678733 0.0))
((0 . "LINE") (100 . "AcDbEntity") (8 . "LOUVERS") (62 . 7) (370 . 13) (100 . "AcDbLine") (10 13731.2104072398
2194.5701357466 0.0) (11 13731.2104072398 972.850678733 0.0))
((0 . "LINE") (100 . "AcDbEntity") (8 . "LOUVERS") (62 . 7) (370 . 13) (100 . "AcDbLine") (10 13766.1990950226
2194.5701357466 0.0) (11 13766.1990950226 972.850678733 0.0))
((0 . "LINE") (100 . "AcDbEntity") (8 . "LOUVERS") (62 . 7) (370 . 13) (100 . "AcDbLine") (10 15361.9909502262
2194.5701357466 0.0) (11 15409.1063348416 2194.5701357466 0.0))
((0 . "LINE") (100 . "AcDbEntity") (8 . "LOUVERS") (62 . 7) (370 . 13) (100 . "AcDbLine") (10 15409.1063348416
2194.5701357466 0.0) (11 15438.2126696833 2194.5701357466 0.0))
((0 . "LINE") (100 . "AcDbEntity") (8 . "LOUVERS") (62 . 7) (370 . 13) (100 . "AcDbLine") (10 15438.2126696833
2194.5701357466 0.0) (11 15487.556561086 2194.5701357466 0.0))
((0 . "LINE") (100 . "AcDbEntity") (8 . "LOUVERS") (62 . 7) (370 . 13) (100 . "AcDbLine") (10 15487.556561086
2194.5701357466 0.0) (11 15528.0429864253 2194.5701357466 0.0))
((0 . "LINE") (100 . "AcDbEntity") (8 . "LOUVERS") (62 . 7) (370 . 13) (100 . "AcDbLine") (10 15528.0429864253
2194.5701357466 0.0) (11 15554.6606334842 2194.5701357466 0.0))
((0 . "LINE") (100 . "AcDbEntity") (8 . "LOUVERS") (62 . 7) (370 . 13) (100 . "AcDbLine") (10 15554.6606334842
2194.5701357466 0.0) (11 15588.257918552 2194.5701357466 0.0))
((0 . "LINE") (100 . "AcDbEntity") (8 . "LOUVERS") (62 . 7) (370 . 13) (100 . "AcDbLine") (10 15588.257918552
2194.5701357466 0.0) (11 15613.371040724 2194.5701357466 0.0))
((0 . "LINE") (100 . "AcDbEntity") (8 . "LOUVERS") (62 . 7) (370 . 13) (100 . "AcDbLine") (10 15613.371040724
2194.5701357466 0.0) (11 15664.6606334842 2194.5701357466 0.0))
((0 . "LINE") (100 . "AcDbEntity") (8 . "LOUVERS") (62 . 7) (370 . 13) (100 . "AcDbLine") (10 15664.6606334842
2194.5701357466 0.0) (11 15690.0452488688 2194.5701357466 0.0))
((0 . "LINE") (100 . "AcDbEntity") (8 . "LOUVERS") (62 . 7) (370 . 13) (100 . "AcDbLine") (10 15690.0452488688
2194.5701357466 0.0) (11 15690.0452488688 972.850678733 0.0))
((0 . "LINE") (100 . "AcDbEntity") (8 . "LOUVERS") (62 . 7) (370 . 13) (100 . "AcDbLine") (10 15690.0452488688
972.850678733 0.0) (11 15664.6606334842 972.850678733 0.0))
((0 . "LINE") (100 . "AcDbEntity") (8 . "LOUVERS") (62 . 7) (370 . 13) (100 . "AcDbLine") (10 15664.6606334842
972.850678733 0.0) (11 15613.371040724 972.850678733 0.0))
((0 . "LINE") (100 . "AcDbEntity") (8 . "LOUVERS") (62 . 7) (370 . 13) (100 . "AcDbLine") (10 15613.371040724
972.850678733 0.0) (11 15588.257918552 972.850678733 0.0))
((0 . "LINE") (100 . "AcDbEntity") (8 . "LOUVERS") (62 . 7) (370 . 13) (100 . "AcDbLine") (10 15588.257918552
972.850678733 0.0) (11 15554.6606334842 972.850678733 0.0))
((0 . "LINE") (100 . "AcDbEntity") (8 . "LOUVERS") (62 . 7) (370 . 13) (100 . "AcDbLine") (10 15554.6606334842
972.850678733 0.0) (11 15528.0429864253 972.850678733 0.0))
((0 . "LINE") (100 . "AcDbEntity") (8 . "LOUVERS") (62 . 7) (370 . 13) (100 . "AcDbLine") (10 15528.0429864253
972.850678733 0.0) (11 15487.556561086 972.850678733 0.0))
((0 . "LINE") (100 . "AcDbEntity") (8 . "LOUVERS") (62 . 7) (370 . 13) (100 . "AcDbLine") (10 15487.556561086
972.850678733 0.0) (11 15438.2126696833 972.850678733 0.0))
((0 . "LINE") (100 . "AcDbEntity") (8 . "LOUVERS") (62 . 7) (370 . 13) (100 . "AcDbLine") (10 15438.2126696833
972.850678733 0.0) (11 15409.1063348416 972.850678733 0.0))
((0 . "LINE") (100 . "AcDbEntity") (8 . "LOUVERS") (62 . 7) (370 . 13) (100 . "AcDbLine") (10 15409.1063348416
972.850678733 0.0) (11 15361.9909502262 972.850678733 0.0))
((0 . "LINE") (100 . "AcDbEntity") (8 . "LOUVERS") (62 . 7) (370 . 13) (100 . "AcDbLine") (10 15361.9909502262
972.850678733 0.0) (11 15361.9909502262 2183.257918552 0.0))
((0 . "LINE") (100 . "AcDbEntity") (8 . "LOUVERS") (62 . 7) (370 . 13) (100 . "AcDbLine") (10 15361.9909502262
2183.257918552 0.0) (11 15361.9909502262 2194.5701357466 0.0))
((0 . "LINE") (100 . "AcDbEntity") (8 . "LOUVERS") (62 . 7) (370 . 13) (100 . "AcDbLine") (10 15409.1063348416
2194.5701357466 0.0) (11 15409.1063348416 972.850678733 0.0))
((0 . "LINE") (100 . "AcDbEntity") (8 . "LOUVERS") (62 . 7) (370 . 13) (100 . "AcDbLine") (10 15438.2126696833
2194.5701357466 0.0) (11 15438.2126696833 972.850678733 0.0))
((0 . "LINE") (100 . "AcDbEntity") (8 . "LOUVERS") (62 . 7) (370 . 13) (100 . "AcDbLine") (10 15487.556561086
2194.5701357466 0.0) (11 15487.556561086 972.850678733 0.0))
((0 . "LINE") (100 . "AcDbEntity") (8 . "LOUVERS") (62 . 7) (370 . 13) (100 . "AcDbLine") (10 15528.0429864253
2194.5701357466 0.0) (11 15528.0429864253 972.850678733 0.0))
((0 . "LINE") (100 . "AcDbEntity") (8 . "LOUVERS") (62 . 7) (370 . 13) (100 . "AcDbLine") (10 15554.6606334842
2194.5701357466 0.0) (11 15554.6606334842 972.850678733 0.0))
((0 . "LINE") (100 . "AcDbEntity") (8 . "LOUVERS") (62 . 7) (370 . 13) (100 . "AcDbLine") (10 15588.257918552
2194.5701357466 0.0) (11 15588.257918552 972.850678733 0.0))
((0 . "LINE") (100 . "AcDbEntity") (8 . "LOUVERS") (62 . 7) (370 . 13) (100 . "AcDbLine") (10 15613.371040724
2194.5701357466 0.0) (11 15613.371040724 972.850678733 0.0))
((0 . "LINE") (100 . "AcDbEntity") (8 . "LOUVERS") (62 . 7) (370 . 13) (100 . "AcDbLine") (10 15664.6606334842
2194.5701357466 0.0) (11 15664.6606334842 972.850678733 0.0))
((0 . "LINE") (100 . "AcDbEntity") (8 . "LOUVERS") (62 . 7) (370 . 13) (100 . "AcDbLine") (10 1018.0995475113
5180.9954751131 0.0) (11 1065.1696832579 5180.9954751131 0.0))
((0 . "LINE") (100 . "AcDbEntity") (8 . "LOUVERS") (62 . 7) (370 . 13) (100 . "AcDbLine") (10 1065.1696832579
5180.9954751131 0.0) (11 1091.3122171946 5180.9954751131 0.0))
((0 . "LINE") (100 . "AcDbEntity") (8 . "LOUVERS") (62 . 7) (370 . 13) (100 . "AcDbLine") (10 1091.3122171946
5180.9954751131 0.0) (11 1133.7443438914 5180.9954751131 0.0))
((0 . "LINE") (100 . "AcDbEntity") (8 . "LOUVERS") (62 . 7) (370 . 13) (100 . "AcDbLine") (10 1133.7443438914
5180.9954751131 0.0) (11 1190.1470588235 5180.9954751131 0.0))
((0 . "LINE") (100 . "AcDbEntity") (8 . "LOUVERS") (62 . 7) (370 . 13) (100 . "AcDbLine") (10 1190.1470588235
5180.9954751131 0.0) (11 1207.1380090498 5180.9954751131 0.0))
((0 . "LINE") (100 . "AcDbEntity") (8 . "LOUVERS") (62 . 7) (370 . 13) (100 . "AcDbLine") (10 1207.1380090498
5180.9954751131 0.0) (11 1253.1674208145 5180.9954751131 0.0))
((0 . "LINE") (100 . "AcDbEntity") (8 . "LOUVERS") (62 . 7) (370 . 13) (100 . "AcDbLine") (10 1253.1674208145
5180.9954751131 0.0) (11 1302.2737556561 5180.9954751131 0.0))
((0 . "LINE") (100 . "AcDbEntity") (8 . "LOUVERS") (62 . 7) (370 . 13) (100 . "AcDbLine") (10 1302.2737556561
5180.9954751131 0.0) (11 1321.2895927602 5180.9954751131 0.0))
((0 . "LINE") (100 . "AcDbEntity") (8 . "LOUVERS") (62 . 7) (370 . 13) (100 . "AcDbLine") (10 1321.2895927602
5180.9954751131 0.0) (11 1334.8416289593 5180.9954751131 0.0))
((0 . "LINE") (100 . "AcDbEntity") (8 . "LOUVERS") (62 . 7) (370 . 13) (100 . "AcDbLine") (10 1334.8416289593
5180.9954751131 0.0) (11 1334.8416289593 3891.4027149321 0.0))
((0 . "LINE") (100 . "AcDbEntity") (8 . "LOUVERS") (62 . 7) (370 . 13) (100 . "AcDbLine") (10 1334.8416289593
3891.4027149321 0.0) (11 1321.2895927602 3891.4027149321 0.0))
((0 . "LINE") (100 . "AcDbEntity") (8 . "LOUVERS") (62 . 7) (370 . 13) (100 . "AcDbLine") (10 1321.2895927602
3891.4027149321 0.0) (11 1302.2737556561 3891.4027149321 0.0))
((0 . "LINE") (100 . "AcDbEntity") (8 . "LOUVERS") (62 . 7) (370 . 13) (100 . "AcDbLine") (10 1302.2737556561
3891.4027149321 0.0) (11 1253.1674208145 3891.4027149321 0.0))
((0 . "LINE") (100 . "AcDbEntity") (8 . "LOUVERS") (62 . 7) (370 . 13) (100 . "AcDbLine") (10 1253.1674208145
3891.4027149321 0.0) (11 1207.1380090498 3891.4027149321 0.0))
((0 . "LINE") (100 . "AcDbEntity") (8 . "LOUVERS") (62 . 7) (370 . 13) (100 . "AcDbLine") (10 1207.1380090498
3891.4027149321 0.0) (11 1190.1470588235 3891.4027149321 0.0))
((0 . "LINE") (100 . "AcDbEntity") (8 . "LOUVERS") (62 . 7) (370 . 13) (100 . "AcDbLine") (10 1190.1470588235
3891.4027149321 0.0) (11 1133.7443438914 3891.4027149321 0.0))
((0 . "LINE") (100 . "AcDbEntity") (8 . "LOUVERS") (62 . 7) (370 . 13) (100 . "AcDbLine") (10 1133.7443438914
3891.4027149321 0.0) (11 1091.3122171946 3891.4027149321 0.0))
((0 . "LINE") (100 . "AcDbEntity") (8 . "LOUVERS") (62 . 7) (370 . 13) (100 . "AcDbLine") (10 1091.3122171946
3891.4027149321 0.0) (11 1065.1696832579 3891.4027149321 0.0))
((0 . "LINE") (100 . "AcDbEntity") (8 . "LOUVERS") (62 . 7) (370 . 13) (100 . "AcDbLine") (10 1065.1696832579
3891.4027149321 0.0) (11 1018.0995475113 3891.4027149321 0.0))
((0 . "LINE") (100 . "AcDbEntity") (8 . "LOUVERS") (62 . 7) (370 . 13) (100 . "AcDbLine") (10 1018.0995475113
3891.4027149321 0.0) (11 1018.0995475113 4457.0135746606 0.0))
((0 . "LINE") (100 . "AcDbEntity") (8 . "LOUVERS") (62 . 7) (370 . 13) (100 . "AcDbLine") (10 1018.0995475113
4457.0135746606 0.0) (11 1018.0995475113 4819.0045248869 0.0))
((0 . "LINE") (100 . "AcDbEntity") (8 . "LOUVERS") (62 . 7) (370 . 13) (100 . "AcDbLine") (10 1018.0995475113
4819.0045248869 0.0) (11 1018.0995475113 5180.9954751131 0.0))
((0 . "LINE") (100 . "AcDbEntity") (8 . "LOUVERS") (62 . 7) (370 . 13) (100 . "AcDbLine") (10 1065.1696832579
5180.9954751131 0.0) (11 1065.1696832579 3891.4027149321 0.0))
((0 . "LINE") (100 . "AcDbEntity") (8 . "LOUVERS") (62 . 7) (370 . 13) (100 . "AcDbLine") (10 1091.3122171946
5180.9954751131 0.0) (11 1091.3122171946 3891.4027149321 0.0))
((0 . "LINE") (100 . "AcDbEntity") (8 . "LOUVERS") (62 . 7) (370 . 13) (100 . "AcDbLine") (10 1133.7443438914
5180.9954751131 0.0) (11 1133.7443438914 3891.4027149321 0.0))
((0 . "LINE") (100 . "AcDbEntity") (8 . "LOUVERS") (62 . 7) (370 . 13) (100 . "AcDbLine") (10 1190.1470588235
5180.9954751131 0.0) (11 1190.1470588235 3891.4027149321 0.0))
((0 . "LINE") (100 . "AcDbEntity") (8 . "LOUVERS") (62 . 7) (370 . 13) (100 . "AcDbLine") (10 1207.1380090498
5180.9954751131 0.0) (11 1207.1380090498 3891.4027149321 0.0))
((0 . "LINE") (100 . "AcDbEntity") (8 . "LOUVERS") (62 . 7) (370 . 13) (100 . "AcDbLine") (10 1253.1674208145
5180.9954751131 0.0) (11 1253.1674208145 3891.4027149321 0.0))
((0 . "LINE") (100 . "AcDbEntity") (8 . "LOUVERS") (62 . 7) (370 . 13) (100 . "AcDbLine") (10 1302.2737556561
5180.9954751131 0.0) (11 1302.2737556561 3891.4027149321 0.0))
((0 . "LINE") (100 . "AcDbEntity") (8 . "LOUVERS") (62 . 7) (370 . 13) (100 . "AcDbLine") (10 1321.2895927602
5180.9954751131 0.0) (11 1321.2895927602 3891.4027149321 0.0))
((0 . "LINE") (100 . "AcDbEntity") (8 . "LOUVERS") (62 . 7) (370 . 13) (100 . "AcDbLine") (10 2352.9411764706
5180.9954751131 0.0) (11 2402.5452488688 5180.9954751131 0.0))
((0 . "LINE") (100 . "AcDbEntity") (8 . "LOUVERS") (62 . 7) (370 . 13) (100 . "AcDbLine") (10 2402.5452488688
5180.9954751131 0.0) (11 2475.4751131222 5180.9954751131 0.0))
((0 . "LINE") (100 . "AcDbEntity") (8 . "LOUVERS") (62 . 7) (370 . 13) (100 . "AcDbLine") (10 2475.4751131222
5180.9954751131 0.0) (11 2531.0633484163 5180.9954751131 0.0))
((0 . "LINE") (100 . "AcDbEntity") (8 . "LOUVERS") (62 . 7) (370 . 13) (100 . "AcDbLine") (10 2531.0633484163
5180.9954751131 0.0) (11 2567.3755656109 5180.9954751131 0.0))
((0 . "LINE") (100 . "AcDbEntity") (8 . "LOUVERS") (62 . 7) (370 . 13) (100 . "AcDbLine") (10 2567.3755656109
5180.9954751131 0.0) (11 2613.6990950226 5180.9954751131 0.0))
((0 . "LINE") (100 . "AcDbEntity") (8 . "LOUVERS") (62 . 7) (370 . 13) (100 . "AcDbLine") (10 2613.6990950226
5180.9954751131 0.0) (11 2635.5090497738 5180.9954751131 0.0))
((0 . "LINE") (100 . "AcDbEntity") (8 . "LOUVERS") (62 . 7) (370 . 13) (100 . "AcDbLine") (10 2635.5090497738
5180.9954751131 0.0) (11 2680.9954751131 5180.9954751131 0.0))
((0 . "LINE") (100 . "AcDbEntity") (8 . "LOUVERS") (62 . 7) (370 . 13) (100 . "AcDbLine") (10 2680.9954751131
5180.9954751131 0.0) (11 2680.9954751131 4819.0045248869 0.0))
((0 . "LINE") (100 . "AcDbEntity") (8 . "LOUVERS") (62 . 7) (370 . 13) (100 . "AcDbLine") (10 2680.9954751131
4819.0045248869 0.0) (11 2680.9954751131 4457.0135746606 0.0))
((0 . "LINE") (100 . "AcDbEntity") (8 . "LOUVERS") (62 . 7) (370 . 13) (100 . "AcDbLine") (10 2680.9954751131
4457.0135746606 0.0) (11 2680.9954751131 3891.4027149321 0.0))
((0 . "LINE") (100 . "AcDbEntity") (8 . "LOUVERS") (62 . 7) (370 . 13) (100 . "AcDbLine") (10 2680.9954751131
3891.4027149321 0.0) (11 2635.5090497738 3891.4027149321 0.0))
((0 . "LINE") (100 . "AcDbEntity") (8 . "LOUVERS") (62 . 7) (370 . 13) (100 . "AcDbLine") (10 2635.5090497738
3891.4027149321 0.0) (11 2613.6990950226 3891.4027149321 0.0))
((0 . "LINE") (100 . "AcDbEntity") (8 . "LOUVERS") (62 . 7) (370 . 13) (100 . "AcDbLine") (10 2613.6990950226
3891.4027149321 0.0) (11 2567.3755656109 3891.4027149321 0.0))
((0 . "LINE") (100 . "AcDbEntity") (8 . "LOUVERS") (62 . 7) (370 . 13) (100 . "AcDbLine") (10 2567.3755656109
3891.4027149321 0.0) (11 2531.0633484163 3891.4027149321 0.0))
((0 . "LINE") (100 . "AcDbEntity") (8 . "LOUVERS") (62 . 7) (370 . 13) (100 . "AcDbLine") (10 2531.0633484163
3891.4027149321 0.0) (11 2475.4751131222 3891.4027149321 0.0))
((0 . "LINE") (100 . "AcDbEntity") (8 . "LOUVERS") (62 . 7) (370 . 13) (100 . "AcDbLine") (10 2475.4751131222
3891.4027149321 0.0) (11 2402.5452488688 3891.4027149321 0.0))
((0 . "LINE") (100 . "AcDbEntity") (8 . "LOUVERS") (62 . 7) (370 . 13) (100 . "AcDbLine") (10 2402.5452488688
3891.4027149321 0.0) (11 2352.9411764706 3891.4027149321 0.0))
((0 . "LINE") (100 . "AcDbEntity") (8 . "LOUVERS") (62 . 7) (370 . 13) (100 . "AcDbLine") (10 2352.9411764706
3891.4027149321 0.0) (11 2352.9411764706 5180.9954751131 0.0))
((0 . "LINE") (100 . "AcDbEntity") (8 . "LOUVERS") (62 . 7) (370 . 13) (100 . "AcDbLine") (10 2402.5452488688
5180.9954751131 0.0) (11 2402.5452488688 3891.4027149321 0.0))
((0 . "LINE") (100 . "AcDbEntity") (8 . "LOUVERS") (62 . 7) (370 . 13) (100 . "AcDbLine") (10 2475.4751131222
5180.9954751131 0.0) (11 2475.4751131222 3891.4027149321 0.0))
((0 . "LINE") (100 . "AcDbEntity") (8 . "LOUVERS") (62 . 7) (370 . 13) (100 . "AcDbLine") (10 2531.0633484163
5180.9954751131 0.0) (11 2531.0633484163 3891.4027149321 0.0))
((0 . "LINE") (100 . "AcDbEntity") (8 . "LOUVERS") (62 . 7) (370 . 13) (100 . "AcDbLine") (10 2567.3755656109
5180.9954751131 0.0) (11 2567.3755656109 3891.4027149321 0.0))
((0 . "LINE") (100 . "AcDbEntity") (8 . "LOUVERS") (62 . 7) (370 . 13) (100 . "AcDbLine") (10 2613.6990950226
5180.9954751131 0.0) (11 2613.6990950226 3891.4027149321 0.0))
((0 . "LINE") (100 . "AcDbEntity") (8 . "LOUVERS") (62 . 7) (370 . 13) (100 . "AcDbLine") (10 2635.5090497738
5180.9954751131 0.0) (11 2635.5090497738 3891.4027149321 0.0))
((0 . "LINE") (100 . "AcDbEntity") (8 . "LOUVERS") (62 . 7) (370 . 13) (100 . "AcDbLine") (10 1018.0995475113
2352.9411764706 0.0) (11 1062.4208144796 2352.9411764706 0.0))
((0 . "LINE") (100 . "AcDbEntity") (8 . "LOUVERS") (62 . 7) (370 . 13) (100 . "AcDbLine") (10 1062.4208144796
2352.9411764706 0.0) (11 1088.6085972851 2352.9411764706 0.0))
((0 . "LINE") (100 . "AcDbEntity") (8 . "LOUVERS") (62 . 7) (370 . 13) (100 . "AcDbLine") (10 1088.6085972851
2352.9411764706 0.0) (11 1132.8280542986 2352.9411764706 0.0))
((0 . "LINE") (100 . "AcDbEntity") (8 . "LOUVERS") (62 . 7) (370 . 13) (100 . "AcDbLine") (10 1132.8280542986
2352.9411764706 0.0) (11 1188.9366515837 2352.9411764706 0.0))
((0 . "LINE") (100 . "AcDbEntity") (8 . "LOUVERS") (62 . 7) (370 . 13) (100 . "AcDbLine") (10 1188.9366515837
2352.9411764706 0.0) (11 1207.1606334842 2352.9411764706 0.0))
((0 . "LINE") (100 . "AcDbEntity") (8 . "LOUVERS") (62 . 7) (370 . 13) (100 . "AcDbLine") (10 1207.1606334842
2352.9411764706 0.0) (11 1251.4027149321 2352.9411764706 0.0))
((0 . "LINE") (100 . "AcDbEntity") (8 . "LOUVERS") (62 . 7) (370 . 13) (100 . "AcDbLine") (10 1251.4027149321
2352.9411764706 0.0) (11 1302.9411764706 2352.9411764706 0.0))
((0 . "LINE") (100 . "AcDbEntity") (8 . "LOUVERS") (62 . 7) (370 . 13) (100 . "AcDbLine") (10 1302.9411764706
2352.9411764706 0.0) (11 1320.6447963801 2352.9411764706 0.0))
((0 . "LINE") (100 . "AcDbEntity") (8 . "LOUVERS") (62 . 7) (370 . 13) (100 . "AcDbLine") (10 1320.6447963801
2352.9411764706 0.0) (11 1334.8416289593 2352.9411764706 0.0))
((0 . "LINE") (100 . "AcDbEntity") (8 . "LOUVERS") (62 . 7) (370 . 13) (100 . "AcDbLine") (10 1334.8416289593
2352.9411764706 0.0) (11 1334.8416289593 1063.3484162896 0.0))
((0 . "LINE") (100 . "AcDbEntity") (8 . "LOUVERS") (62 . 7) (370 . 13) (100 . "AcDbLine") (10 1334.8416289593
1063.3484162896 0.0) (11 1320.6447963801 1063.3484162896 0.0))
((0 . "LINE") (100 . "AcDbEntity") (8 . "LOUVERS") (62 . 7) (370 . 13) (100 . "AcDbLine") (10 1320.6447963801
1063.3484162896 0.0) (11 1302.9411764706 1063.3484162896 0.0))
((0 . "LINE") (100 . "AcDbEntity") (8 . "LOUVERS") (62 . 7) (370 . 13) (100 . "AcDbLine") (10 1302.9411764706
1063.3484162896 0.0) (11 1251.4027149321 1063.3484162896 0.0))
((0 . "LINE") (100 . "AcDbEntity") (8 . "LOUVERS") (62 . 7) (370 . 13) (100 . "AcDbLine") (10 1251.4027149321
1063.3484162896 0.0) (11 1207.1606334842 1063.3484162896 0.0))
((0 . "LINE") (100 . "AcDbEntity") (8 . "LOUVERS") (62 . 7) (370 . 13) (100 . "AcDbLine") (10 1207.1606334842
1063.3484162896 0.0) (11 1188.9366515837 1063.3484162896 0.0))
((0 . "LINE") (100 . "AcDbEntity") (8 . "LOUVERS") (62 . 7) (370 . 13) (100 . "AcDbLine") (10 1188.9366515837
1063.3484162896 0.0) (11 1132.8280542986 1063.3484162896 0.0))
((0 . "LINE") (100 . "AcDbEntity") (8 . "LOUVERS") (62 . 7) (370 . 13) (100 . "AcDbLine") (10 1132.8280542986
1063.3484162896 0.0) (11 1088.6085972851 1063.3484162896 0.0))
((0 . "LINE") (100 . "AcDbEntity") (8 . "LOUVERS") (62 . 7) (370 . 13) (100 . "AcDbLine") (10 1088.6085972851
1063.3484162896 0.0) (11 1062.4208144796 1063.3484162896 0.0))
((0 . "LINE") (100 . "AcDbEntity") (8 . "LOUVERS") (62 . 7) (370 . 13) (100 . "AcDbLine") (10 1062.4208144796
1063.3484162896 0.0) (11 1018.0995475113 1063.3484162896 0.0))
((0 . "LINE") (100 . "AcDbEntity") (8 . "LOUVERS") (62 . 7) (370 . 13) (100 . "AcDbLine") (10 1018.0995475113
1063.3484162896 0.0) (11 1018.0995475113 1651.5837104072 0.0))
((0 . "LINE") (100 . "AcDbEntity") (8 . "LOUVERS") (62 . 7) (370 . 13) (100 . "AcDbLine") (10 1018.0995475113
1651.5837104072 0.0) (11 1018.0995475113 2047.5113122172 0.0))
((0 . "LINE") (100 . "AcDbEntity") (8 . "LOUVERS") (62 . 7) (370 . 13) (100 . "AcDbLine") (10 1018.0995475113
2047.5113122172 0.0) (11 1018.0995475113 2352.9411764706 0.0))
((0 . "LINE") (100 . "AcDbEntity") (8 . "LOUVERS") (62 . 7) (370 . 13) (100 . "AcDbLine") (10 1062.4208144796
2352.9411764706 0.0) (11 1062.4208144796 1063.3484162896 0.0))
((0 . "LINE") (100 . "AcDbEntity") (8 . "LOUVERS") (62 . 7) (370 . 13) (100 . "AcDbLine") (10 1088.6085972851
2352.9411764706 0.0) (11 1088.6085972851 1063.3484162896 0.0))
((0 . "LINE") (100 . "AcDbEntity") (8 . "LOUVERS") (62 . 7) (370 . 13) (100 . "AcDbLine") (10 1132.8280542986
2352.9411764706 0.0) (11 1132.8280542986 1063.3484162896 0.0))
((0 . "LINE") (100 . "AcDbEntity") (8 . "LOUVERS") (62 . 7) (370 . 13) (100 . "AcDbLine") (10 1188.9366515837
2352.9411764706 0.0) (11 1188.9366515837 1063.3484162896 0.0))
((0 . "LINE") (100 . "AcDbEntity") (8 . "LOUVERS") (62 . 7) (370 . 13) (100 . "AcDbLine") (10 1207.1606334842
2352.9411764706 0.0) (11 1207.1606334842 1063.3484162896 0.0))
((0 . "LINE") (100 . "AcDbEntity") (8 . "LOUVERS") (62 . 7) (370 . 13) (100 . "AcDbLine") (10 1251.4027149321
2352.9411764706 0.0) (11 1251.4027149321 1063.3484162896 0.0))
((0 . "LINE") (100 . "AcDbEntity") (8 . "LOUVERS") (62 . 7) (370 . 13) (100 . "AcDbLine") (10 1302.9411764706
2352.9411764706 0.0) (11 1302.9411764706 1063.3484162896 0.0))
((0 . "LINE") (100 . "AcDbEntity") (8 . "LOUVERS") (62 . 7) (370 . 13) (100 . "AcDbLine") (10 1320.6447963801
2352.9411764706 0.0) (11 1320.6447963801 1063.3484162896 0.0))
((0 . "LINE") (100 . "AcDbEntity") (8 . "LOUVERS") (62 . 7) (370 . 13) (100 . "AcDbLine") (10 2352.9411764706
2352.9411764706 0.0) (11 2402.7601809955 2352.9411764706 0.0))
((0 . "LINE") (100 . "AcDbEntity") (8 . "LOUVERS") (62 . 7) (370 . 13) (100 . "AcDbLine") (10 2402.7601809955
2352.9411764706 0.0) (11 2420.9049773756 2352.9411764706 0.0))
((0 . "LINE") (100 . "AcDbEntity") (8 . "LOUVERS") (62 . 7) (370 . 13) (100 . "AcDbLine") (10 2420.9049773756
2352.9411764706 0.0) (11 2475.0113122172 2352.9411764706 0.0))
((0 . "LINE") (100 . "AcDbEntity") (8 . "LOUVERS") (62 . 7) (370 . 13) (100 . "AcDbLine") (10 2475.0113122172
2352.9411764706 0.0) (11 2528.9592760181 2352.9411764706 0.0))
((0 . "LINE") (100 . "AcDbEntity") (8 . "LOUVERS") (62 . 7) (370 . 13) (100 . "AcDbLine") (10 2528.9592760181
2352.9411764706 0.0) (11 2567.6018099548 2352.9411764706 0.0))
((0 . "LINE") (100 . "AcDbEntity") (8 . "LOUVERS") (62 . 7) (370 . 13) (100 . "AcDbLine") (10 2567.6018099548
2352.9411764706 0.0) (11 2613.2918552036 2352.9411764706 0.0))
((0 . "LINE") (100 . "AcDbEntity") (8 . "LOUVERS") (62 . 7) (370 . 13) (100 . "AcDbLine") (10 2613.2918552036
2352.9411764706 0.0) (11 2635.2488687783 2352.9411764706 0.0))
((0 . "LINE") (100 . "AcDbEntity") (8 . "LOUVERS") (62 . 7) (370 . 13) (100 . "AcDbLine") (10 2635.2488687783
2352.9411764706 0.0) (11 2680.9954751131 2352.9411764706 0.0))
((0 . "LINE") (100 . "AcDbEntity") (8 . "LOUVERS") (62 . 7) (370 . 13) (100 . "AcDbLine") (10 2680.9954751131
2352.9411764706 0.0) (11 2680.9954751131 2047.5113122172 0.0))
((0 . "LINE") (100 . "AcDbEntity") (8 . "LOUVERS") (62 . 7) (370 . 13) (100 . "AcDbLine") (10 2680.9954751131
2047.5113122172 0.0) (11 2680.9954751131 1651.5837104072 0.0))
((0 . "LINE") (100 . "AcDbEntity") (8 . "LOUVERS") (62 . 7) (370 . 13) (100 . "AcDbLine") (10 2680.9954751131
1651.5837104072 0.0) (11 2680.9954751131 1063.3484162896 0.0))
((0 . "LINE") (100 . "AcDbEntity") (8 . "LOUVERS") (62 . 7) (370 . 13) (100 . "AcDbLine") (10 2680.9954751131
1063.3484162896 0.0) (11 2635.2488687783 1063.3484162896 0.0))
((0 . "LINE") (100 . "AcDbEntity") (8 . "LOUVERS") (62 . 7) (370 . 13) (100 . "AcDbLine") (10 2635.2488687783
1063.3484162896 0.0) (11 2613.2918552036 1063.3484162896 0.0))
((0 . "LINE") (100 . "AcDbEntity") (8 . "LOUVERS") (62 . 7) (370 . 13) (100 . "AcDbLine") (10 2613.2918552036
1063.3484162896 0.0) (11 2567.6018099548 1063.3484162896 0.0))
((0 . "LINE") (100 . "AcDbEntity") (8 . "LOUVERS") (62 . 7) (370 . 13) (100 . "AcDbLine") (10 2567.6018099548
1063.3484162896 0.0) (11 2528.9592760181 1063.3484162896 0.0))
((0 . "LINE") (100 . "AcDbEntity") (8 . "LOUVERS") (62 . 7) (370 . 13) (100 . "AcDbLine") (10 2528.9592760181
1063.3484162896 0.0) (11 2475.0113122172 1063.3484162896 0.0))
((0 . "LINE") (100 . "AcDbEntity") (8 . "LOUVERS") (62 . 7) (370 . 13) (100 . "AcDbLine") (10 2475.0113122172
1063.3484162896 0.0) (11 2420.9049773756 1063.3484162896 0.0))
((0 . "LINE") (100 . "AcDbEntity") (8 . "LOUVERS") (62 . 7) (370 . 13) (100 . "AcDbLine") (10 2420.9049773756
1063.3484162896 0.0) (11 2402.7601809955 1063.3484162896 0.0))
((0 . "LINE") (100 . "AcDbEntity") (8 . "LOUVERS") (62 . 7) (370 . 13) (100 . "AcDbLine") (10 2402.7601809955
1063.3484162896 0.0) (11 2352.9411764706 1063.3484162896 0.0))
((0 . "LINE") (100 . "AcDbEntity") (8 . "LOUVERS") (62 . 7) (370 . 13) (100 . "AcDbLine") (10 2352.9411764706
1063.3484162896 0.0) (11 2352.9411764706 2352.9411764706 0.0))
((0 . "LINE") (100 . "AcDbEntity") (8 . "LOUVERS") (62 . 7) (370 . 13) (100 . "AcDbLine") (10 2402.7601809955
2352.9411764706 0.0) (11 2402.7601809955 1063.3484162896 0.0))
((0 . "LINE") (100 . "AcDbEntity") (8 . "LOUVERS") (62 . 7) (370 . 13) (100 . "AcDbLine") (10 2420.9049773756
2352.9411764706 0.0) (11 2420.9049773756 1063.3484162896 0.0))
((0 . "LINE") (100 . "AcDbEntity") (8 . "LOUVERS") (62 . 7) (370 . 13) (100 . "AcDbLine") (10 2475.0113122172
2352.9411764706 0.0) (11 2475.0113122172 1063.3484162896 0.0))
((0 . "LINE") (100 . "AcDbEntity") (8 . "LOUVERS") (62 . 7) (370 . 13) (100 . "AcDbLine") (10 2528.9592760181
2352.9411764706 0.0) (11 2528.9592760181 1063.3484162896 0.0))
((0 . "LINE") (100 . "AcDbEntity") (8 . "LOUVERS") (62 . 7) (370 . 13) (100 . "AcDbLine") (10 2567.6018099548
2352.9411764706 0.0) (11 2567.6018099548 1063.3484162896 0.0))
((0 . "LINE") (100 . "AcDbEntity") (8 . "LOUVERS") (62 . 7) (370 . 13) (100 . "AcDbLine") (10 2613.2918552036
2352.9411764706 0.0) (11 2613.2918552036 1063.3484162896 0.0))
((0 . "LINE") (100 . "AcDbEntity") (8 . "LOUVERS") (62 . 7) (370 . 13) (100 . "AcDbLine") (10 2635.2488687783
2352.9411764706 0.0) (11 2635.2488687783 1063.3484162896 0.0))
((0 . "LINE") (100 . "AcDbEntity") (8 . "LOUVERS") (62 . 7) (370 . 13) (100 . "AcDbLine") (10 17352.9411764706
5180.9954751131 0.0) (11 17376.0746606335 5180.9954751131 0.0))
((0 . "LINE") (100 . "AcDbEntity") (8 . "LOUVERS") (62 . 7) (370 . 13) (100 . "AcDbLine") (10 17376.0746606335
5180.9954751131 0.0) (11 17399.185520362 5180.9954751131 0.0))
((0 . "LINE") (100 . "AcDbEntity") (8 . "LOUVERS") (62 . 7) (370 . 13) (100 . "AcDbLine") (10 17399.185520362
5180.9954751131 0.0) (11 17445.463800905 5180.9954751131 0.0))
((0 . "LINE") (100 . "AcDbEntity") (8 . "LOUVERS") (62 . 7) (370 . 13) (100 . "AcDbLine") (10 17445.463800905
5180.9954751131 0.0) (11 17508.0882352941 5180.9954751131 0.0))
((0 . "LINE") (100 . "AcDbEntity") (8 . "LOUVERS") (62 . 7) (370 . 13) (100 . "AcDbLine") (10 17508.0882352941
5180.9954751131 0.0) (11 17554.8076923077 5180.9954751131 0.0))
((0 . "LINE") (100 . "AcDbEntity") (8 . "LOUVERS") (62 . 7) (370 . 13) (100 . "AcDbLine") (10 17554.8076923077
5180.9954751131 0.0) (11 17604.8416289593 5180.9954751131 0.0))
((0 . "LINE") (100 . "AcDbEntity") (8 . "LOUVERS") (62 . 7) (370 . 13) (100 . "AcDbLine") (10 17604.8416289593
5180.9954751131 0.0) (11 17669.6832579186 5180.9954751131 0.0))
((0 . "LINE") (100 . "AcDbEntity") (8 . "LOUVERS") (62 . 7) (370 . 13) (100 . "AcDbLine") (10 17669.6832579186
5180.9954751131 0.0) (11 17669.6832579186 3891.4027149321 0.0))
((0 . "LINE") (100 . "AcDbEntity") (8 . "LOUVERS") (62 . 7) (370 . 13) (100 . "AcDbLine") (10 17669.6832579186
3891.4027149321 0.0) (11 17604.8416289593 3891.4027149321 0.0))
((0 . "LINE") (100 . "AcDbEntity") (8 . "LOUVERS") (62 . 7) (370 . 13) (100 . "AcDbLine") (10 17604.8416289593
3891.4027149321 0.0) (11 17554.8076923077 3891.4027149321 0.0))
((0 . "LINE") (100 . "AcDbEntity") (8 . "LOUVERS") (62 . 7) (370 . 13) (100 . "AcDbLine") (10 17554.8076923077
3891.4027149321 0.0) (11 17508.0882352941 3891.4027149321 0.0))
((0 . "LINE") (100 . "AcDbEntity") (8 . "LOUVERS") (62 . 7) (370 . 13) (100 . "AcDbLine") (10 17508.0882352941
3891.4027149321 0.0) (11 17445.463800905 3891.4027149321 0.0))
((0 . "LINE") (100 . "AcDbEntity") (8 . "LOUVERS") (62 . 7) (370 . 13) (100 . "AcDbLine") (10 17445.463800905
3891.4027149321 0.0) (11 17399.185520362 3891.4027149321 0.0))
((0 . "LINE") (100 . "AcDbEntity") (8 . "LOUVERS") (62 . 7) (370 . 13) (100 . "AcDbLine") (10 17399.185520362
3891.4027149321 0.0) (11 17376.0746606335 3891.4027149321 0.0))
((0 . "LINE") (100 . "AcDbEntity") (8 . "LOUVERS") (62 . 7) (370 . 13) (100 . "AcDbLine") (10 17376.0746606335
3891.4027149321 0.0) (11 17352.9411764706 3891.4027149321 0.0))
((0 . "LINE") (100 . "AcDbEntity") (8 . "LOUVERS") (62 . 7) (370 . 13) (100 . "AcDbLine") (10 17352.9411764706
3891.4027149321 0.0) (11 17352.9411764706 4457.0135746606 0.0))
((0 . "LINE") (100 . "AcDbEntity") (8 . "LOUVERS") (62 . 7) (370 . 13) (100 . "AcDbLine") (10 17352.9411764706
4457.0135746606 0.0) (11 17352.9411764706 4819.0045248869 0.0))
((0 . "LINE") (100 . "AcDbEntity") (8 . "LOUVERS") (62 . 7) (370 . 13) (100 . "AcDbLine") (10 17352.9411764706
4819.0045248869 0.0) (11 17352.9411764706 5180.9954751131 0.0))
((0 . "LINE") (100 . "AcDbEntity") (8 . "LOUVERS") (62 . 7) (370 . 13) (100 . "AcDbLine") (10 17376.0746606335
5180.9954751131 0.0) (11 17376.0746606335 3891.4027149321 0.0))
((0 . "LINE") (100 . "AcDbEntity") (8 . "LOUVERS") (62 . 7) (370 . 13) (100 . "AcDbLine") (10 17399.185520362
5180.9954751131 0.0) (11 17399.185520362 3891.4027149321 0.0))
((0 . "LINE") (100 . "AcDbEntity") (8 . "LOUVERS") (62 . 7) (370 . 13) (100 . "AcDbLine") (10 17445.463800905
5180.9954751131 0.0) (11 17445.463800905 3891.4027149321 0.0))
((0 . "LINE") (100 . "AcDbEntity") (8 . "LOUVERS") (62 . 7) (370 . 13) (100 . "AcDbLine") (10 17508.0882352941
5180.9954751131 0.0) (11 17508.0882352941 3891.4027149321 0.0))
((0 . "LINE") (100 . "AcDbEntity") (8 . "LOUVERS") (62 . 7) (370 . 13) (100 . "AcDbLine") (10 17554.8076923077
5180.9954751131 0.0) (11 17554.8076923077 3891.4027149321 0.0))
((0 . "LINE") (100 . "AcDbEntity") (8 . "LOUVERS") (62 . 7) (370 . 13) (100 . "AcDbLine") (10 17604.8416289593
5180.9954751131 0.0) (11 17604.8416289593 3891.4027149321 0.0))
((0 . "LINE") (100 . "AcDbEntity") (8 . "LOUVERS") (62 . 7) (370 . 13) (100 . "AcDbLine") (10 18687.7828054299
5180.9954751131 0.0) (11 18761.57239819 5180.9954751131 0.0))
((0 . "LINE") (100 . "AcDbEntity") (8 . "LOUVERS") (62 . 7) (370 . 13) (100 . "AcDbLine") (10 18761.57239819
5180.9954751131 0.0) (11 18806.0859728507 5180.9954751131 0.0))
((0 . "LINE") (100 . "AcDbEntity") (8 . "LOUVERS") (62 . 7) (370 . 13) (100 . "AcDbLine") (10 18806.0859728507
5180.9954751131 0.0) (11 18862.6131221719 5180.9954751131 0.0))
((0 . "LINE") (100 . "AcDbEntity") (8 . "LOUVERS") (62 . 7) (370 . 13) (100 . "AcDbLine") (10 18862.6131221719
5180.9954751131 0.0) (11 18904.4457013575 5180.9954751131 0.0))
((0 . "LINE") (100 . "AcDbEntity") (8 . "LOUVERS") (62 . 7) (370 . 13) (100 . "AcDbLine") (10 18904.4457013575
5180.9954751131 0.0) (11 18923.5633484163 5180.9954751131 0.0))
((0 . "LINE") (100 . "AcDbEntity") (8 . "LOUVERS") (62 . 7) (370 . 13) (100 . "AcDbLine") (10 18923.5633484163
5180.9954751131 0.0) (11 18962.5226244344 5180.9954751131 0.0))
((0 . "LINE") (100 . "AcDbEntity") (8 . "LOUVERS") (62 . 7) (370 . 13) (100 . "AcDbLine") (10 18962.5226244344
5180.9954751131 0.0) (11 18980.3733031674 5180.9954751131 0.0))
((0 . "LINE") (100 . "AcDbEntity") (8 . "LOUVERS") (62 . 7) (370 . 13) (100 . "AcDbLine") (10 18980.3733031674
5180.9954751131 0.0) (11 19015.8371040724 5180.9954751131 0.0))
((0 . "LINE") (100 . "AcDbEntity") (8 . "LOUVERS") (62 . 7) (370 . 13) (100 . "AcDbLine") (10 19015.8371040724
5180.9954751131 0.0) (11 19015.8371040724 4819.0045248869 0.0))
((0 . "LINE") (100 . "AcDbEntity") (8 . "LOUVERS") (62 . 7) (370 . 13) (100 . "AcDbLine") (10 19015.8371040724
4819.0045248869 0.0) (11 19015.8371040724 4457.0135746606 0.0))
((0 . "LINE") (100 . "AcDbEntity") (8 . "LOUVERS") (62 . 7) (370 . 13) (100 . "AcDbLine") (10 19015.8371040724
4457.0135746606 0.0) (11 19015.8371040724 3891.4027149321 0.0))
((0 . "LINE") (100 . "AcDbEntity") (8 . "LOUVERS") (62 . 7) (370 . 13) (100 . "AcDbLine") (10 19015.8371040724
3891.4027149321 0.0) (11 18980.3733031674 3891.4027149321 0.0))
((0 . "LINE") (100 . "AcDbEntity") (8 . "LOUVERS") (62 . 7) (370 . 13) (100 . "AcDbLine") (10 18980.3733031674
3891.4027149321 0.0) (11 18962.5226244344 3891.4027149321 0.0))
((0 . "LINE") (100 . "AcDbEntity") (8 . "LOUVERS") (62 . 7) (370 . 13) (100 . "AcDbLine") (10 18962.5226244344
3891.4027149321 0.0) (11 18923.5633484163 3891.4027149321 0.0))
((0 . "LINE") (100 . "AcDbEntity") (8 . "LOUVERS") (62 . 7) (370 . 13) (100 . "AcDbLine") (10 18923.5633484163
3891.4027149321 0.0) (11 18904.4457013575 3891.4027149321 0.0))
((0 . "LINE") (100 . "AcDbEntity") (8 . "LOUVERS") (62 . 7) (370 . 13) (100 . "AcDbLine") (10 18904.4457013575
3891.4027149321 0.0) (11 18862.6131221719 3891.4027149321 0.0))
((0 . "LINE") (100 . "AcDbEntity") (8 . "LOUVERS") (62 . 7) (370 . 13) (100 . "AcDbLine") (10 18862.6131221719
3891.4027149321 0.0) (11 18806.0859728507 3891.4027149321 0.0))
((0 . "LINE") (100 . "AcDbEntity") (8 . "LOUVERS") (62 . 7) (370 . 13) (100 . "AcDbLine") (10 18806.0859728507
3891.4027149321 0.0) (11 18761.57239819 3891.4027149321 0.0))
((0 . "LINE") (100 . "AcDbEntity") (8 . "LOUVERS") (62 . 7) (370 . 13) (100 . "AcDbLine") (10 18761.57239819
3891.4027149321 0.0) (11 18687.7828054299 3891.4027149321 0.0))
((0 . "LINE") (100 . "AcDbEntity") (8 . "LOUVERS") (62 . 7) (370 . 13) (100 . "AcDbLine") (10 18687.7828054299
3891.4027149321 0.0) (11 18687.7828054299 5180.9954751131 0.0))
((0 . "LINE") (100 . "AcDbEntity") (8 . "LOUVERS") (62 . 7) (370 . 13) (100 . "AcDbLine") (10 18761.57239819
5180.9954751131 0.0) (11 18761.57239819 3891.4027149321 0.0))
((0 . "LINE") (100 . "AcDbEntity") (8 . "LOUVERS") (62 . 7) (370 . 13) (100 . "AcDbLine") (10 18806.0859728507
5180.9954751131 0.0) (11 18806.0859728507 3891.4027149321 0.0))
((0 . "LINE") (100 . "AcDbEntity") (8 . "LOUVERS") (62 . 7) (370 . 13) (100 . "AcDbLine") (10 18862.6131221719
5180.9954751131 0.0) (11 18862.6131221719 3891.4027149321 0.0))
((0 . "LINE") (100 . "AcDbEntity") (8 . "LOUVERS") (62 . 7) (370 . 13) (100 . "AcDbLine") (10 18904.4457013575
5180.9954751131 0.0) (11 18904.4457013575 3891.4027149321 0.0))
((0 . "LINE") (100 . "AcDbEntity") (8 . "LOUVERS") (62 . 7) (370 . 13) (100 . "AcDbLine") (10 18923.5633484163
5180.9954751131 0.0) (11 18923.5633484163 3891.4027149321 0.0))
((0 . "LINE") (100 . "AcDbEntity") (8 . "LOUVERS") (62 . 7) (370 . 13) (100 . "AcDbLine") (10 18962.5226244344
5180.9954751131 0.0) (11 18962.5226244344 3891.4027149321 0.0))
((0 . "LINE") (100 . "AcDbEntity") (8 . "LOUVERS") (62 . 7) (370 . 13) (100 . "AcDbLine") (10 18980.3733031674
5180.9954751131 0.0) (11 18980.3733031674 3891.4027149321 0.0))
((0 . "LINE") (100 . "AcDbEntity") (8 . "LOUVERS") (62 . 7) (370 . 13) (100 . "AcDbLine") (10 17352.9411764706
2352.9411764706 0.0) (11 17375.7918552036 2352.9411764706 0.0))
((0 . "LINE") (100 . "AcDbEntity") (8 . "LOUVERS") (62 . 7) (370 . 13) (100 . "AcDbLine") (10 17375.7918552036
2352.9411764706 0.0) (11 17399.3552036199 2352.9411764706 0.0))
((0 . "LINE") (100 . "AcDbEntity") (8 . "LOUVERS") (62 . 7) (370 . 13) (100 . "AcDbLine") (10 17399.3552036199
2352.9411764706 0.0) (11 17445.4185520362 2352.9411764706 0.0))
((0 . "LINE") (100 . "AcDbEntity") (8 . "LOUVERS") (62 . 7) (370 . 13) (100 . "AcDbLine") (10 17445.4185520362
2352.9411764706 0.0) (11 17507.1153846154 2352.9411764706 0.0))
((0 . "LINE") (100 . "AcDbEntity") (8 . "LOUVERS") (62 . 7) (370 . 13) (100 . "AcDbLine") (10 17507.1153846154
2352.9411764706 0.0) (11 17554.8642533937 2352.9411764706 0.0))
((0 . "LINE") (100 . "AcDbEntity") (8 . "LOUVERS") (62 . 7) (370 . 13) (100 . "AcDbLine") (10 17554.8642533937
2352.9411764706 0.0) (11 17606.0859728507 2352.9411764706 0.0))
((0 . "LINE") (100 . "AcDbEntity") (8 . "LOUVERS") (62 . 7) (370 . 13) (100 . "AcDbLine") (10 17606.0859728507
2352.9411764706 0.0) (11 17669.6832579186 2352.9411764706 0.0))
((0 . "LINE") (100 . "AcDbEntity") (8 . "LOUVERS") (62 . 7) (370 . 13) (100 . "AcDbLine") (10 17669.6832579186
2352.9411764706 0.0) (11 17669.6832579186 1063.3484162896 0.0))
((0 . "LINE") (100 . "AcDbEntity") (8 . "LOUVERS") (62 . 7) (370 . 13) (100 . "AcDbLine") (10 17669.6832579186
1063.3484162896 0.0) (11 17606.0859728507 1063.3484162896 0.0))
((0 . "LINE") (100 . "AcDbEntity") (8 . "LOUVERS") (62 . 7) (370 . 13) (100 . "AcDbLine") (10 17606.0859728507
1063.3484162896 0.0) (11 17554.8642533937 1063.3484162896 0.0))
((0 . "LINE") (100 . "AcDbEntity") (8 . "LOUVERS") (62 . 7) (370 . 13) (100 . "AcDbLine") (10 17554.8642533937
1063.3484162896 0.0) (11 17507.1153846154 1063.3484162896 0.0))
((0 . "LINE") (100 . "AcDbEntity") (8 . "LOUVERS") (62 . 7) (370 . 13) (100 . "AcDbLine") (10 17507.1153846154
1063.3484162896 0.0) (11 17445.4185520362 1063.3484162896 0.0))
((0 . "LINE") (100 . "AcDbEntity") (8 . "LOUVERS") (62 . 7) (370 . 13) (100 . "AcDbLine") (10 17445.4185520362
1063.3484162896 0.0) (11 17399.3552036199 1063.3484162896 0.0))
((0 . "LINE") (100 . "AcDbEntity") (8 . "LOUVERS") (62 . 7) (370 . 13) (100 . "AcDbLine") (10 17399.3552036199
1063.3484162896 0.0) (11 17375.7918552036 1063.3484162896 0.0))
((0 . "LINE") (100 . "AcDbEntity") (8 . "LOUVERS") (62 . 7) (370 . 13) (100 . "AcDbLine") (10 17375.7918552036
1063.3484162896 0.0) (11 17352.9411764706 1063.3484162896 0.0))
((0 . "LINE") (100 . "AcDbEntity") (8 . "LOUVERS") (62 . 7) (370 . 13) (100 . "AcDbLine") (10 17352.9411764706
1063.3484162896 0.0) (11 17352.9411764706 1651.5837104072 0.0))
((0 . "LINE") (100 . "AcDbEntity") (8 . "LOUVERS") (62 . 7) (370 . 13) (100 . "AcDbLine") (10 17352.9411764706
1651.5837104072 0.0) (11 17352.9411764706 2047.5113122172 0.0))
((0 . "LINE") (100 . "AcDbEntity") (8 . "LOUVERS") (62 . 7) (370 . 13) (100 . "AcDbLine") (10 17352.9411764706
2047.5113122172 0.0) (11 17352.9411764706 2352.9411764706 0.0))
((0 . "LINE") (100 . "AcDbEntity") (8 . "LOUVERS") (62 . 7) (370 . 13) (100 . "AcDbLine") (10 17375.7918552036
2352.9411764706 0.0) (11 17375.7918552036 1063.3484162896 0.0))
((0 . "LINE") (100 . "AcDbEntity") (8 . "LOUVERS") (62 . 7) (370 . 13) (100 . "AcDbLine") (10 17399.3552036199
2352.9411764706 0.0) (11 17399.3552036199 1063.3484162896 0.0))
((0 . "LINE") (100 . "AcDbEntity") (8 . "LOUVERS") (62 . 7) (370 . 13) (100 . "AcDbLine") (10 17445.4185520362
2352.9411764706 0.0) (11 17445.4185520362 1063.3484162896 0.0))
((0 . "LINE") (100 . "AcDbEntity") (8 . "LOUVERS") (62 . 7) (370 . 13) (100 . "AcDbLine") (10 17507.1153846154
2352.9411764706 0.0) (11 17507.1153846154 1063.3484162896 0.0))
((0 . "LINE") (100 . "AcDbEntity") (8 . "LOUVERS") (62 . 7) (370 . 13) (100 . "AcDbLine") (10 17554.8642533937
2352.9411764706 0.0) (11 17554.8642533937 1063.3484162896 0.0))
((0 . "LINE") (100 . "AcDbEntity") (8 . "LOUVERS") (62 . 7) (370 . 13) (100 . "AcDbLine") (10 17606.0859728507
2352.9411764706 0.0) (11 17606.0859728507 1063.3484162896 0.0))
((0 . "LINE") (100 . "AcDbEntity") (8 . "LOUVERS") (62 . 7) (370 . 13) (100 . "AcDbLine") (10 18687.7828054299
2352.9411764706 0.0) (11 18696.9796380091 2352.9411764706 0.0))
((0 . "LINE") (100 . "AcDbEntity") (8 . "LOUVERS") (62 . 7) (370 . 13) (100 . "AcDbLine") (10 18696.9796380091
2352.9411764706 0.0) (11 18762.3190045249 2352.9411764706 0.0))
((0 . "LINE") (100 . "AcDbEntity") (8 . "LOUVERS") (62 . 7) (370 . 13) (100 . "AcDbLine") (10 18762.3190045249
2352.9411764706 0.0) (11 18805.056561086 2352.9411764706 0.0))
((0 . "LINE") (100 . "AcDbEntity") (8 . "LOUVERS") (62 . 7) (370 . 13) (100 . "AcDbLine") (10 18805.056561086
2352.9411764706 0.0) (11 18818.9027149321 2352.9411764706 0.0))
((0 . "LINE") (100 . "AcDbEntity") (8 . "LOUVERS") (62 . 7) (370 . 13) (100 . "AcDbLine") (10 18818.9027149321
2352.9411764706 0.0) (11 18859.4230769231 2352.9411764706 0.0))
((0 . "LINE") (100 . "AcDbEntity") (8 . "LOUVERS") (62 . 7) (370 . 13) (100 . "AcDbLine") (10 18859.4230769231
2352.9411764706 0.0) (11 18894.0837104072 2352.9411764706 0.0))
((0 . "LINE") (100 . "AcDbEntity") (8 . "LOUVERS") (62 . 7) (370 . 13) (100 . "AcDbLine") (10 18894.0837104072
2352.9411764706 0.0) (11 18923.1674208145 2352.9411764706 0.0))
((0 . "LINE") (100 . "AcDbEntity") (8 . "LOUVERS") (62 . 7) (370 . 13) (100 . "AcDbLine") (10 18923.1674208145
2352.9411764706 0.0) (11 18962.6696832579 2352.9411764706 0.0))
((0 . "LINE") (100 . "AcDbEntity") (8 . "LOUVERS") (62 . 7) (370 . 13) (100 . "AcDbLine") (10 18962.6696832579
2352.9411764706 0.0) (11 18980.2828054299 2352.9411764706 0.0))
((0 . "LINE") (100 . "AcDbEntity") (8 . "LOUVERS") (62 . 7) (370 . 13) (100 . "AcDbLine") (10 18980.2828054299
2352.9411764706 0.0) (11 19015.8371040724 2352.9411764706 0.0))
((0 . "LINE") (100 . "AcDbEntity") (8 . "LOUVERS") (62 . 7) (370 . 13) (100 . "AcDbLine") (10 19015.8371040724
2352.9411764706 0.0) (11 19015.8371040724 2047.5113122172 0.0))
((0 . "LINE") (100 . "AcDbEntity") (8 . "LOUVERS") (62 . 7) (370 . 13) (100 . "AcDbLine") (10 19015.8371040724
2047.5113122172 0.0) (11 19015.8371040724 1651.5837104072 0.0))
((0 . "LINE") (100 . "AcDbEntity") (8 . "LOUVERS") (62 . 7) (370 . 13) (100 . "AcDbLine") (10 19015.8371040724
1651.5837104072 0.0) (11 19015.8371040724 1063.3484162896 0.0))
((0 . "LINE") (100 . "AcDbEntity") (8 . "LOUVERS") (62 . 7) (370 . 13) (100 . "AcDbLine") (10 19015.8371040724
1063.3484162896 0.0) (11 18980.2828054299 1063.3484162896 0.0))
((0 . "LINE") (100 . "AcDbEntity") (8 . "LOUVERS") (62 . 7) (370 . 13) (100 . "AcDbLine") (10 18980.2828054299
1063.3484162896 0.0) (11 18962.6696832579 1063.3484162896 0.0))
((0 . "LINE") (100 . "AcDbEntity") (8 . "LOUVERS") (62 . 7) (370 . 13) (100 . "AcDbLine") (10 18962.6696832579
1063.3484162896 0.0) (11 18923.1674208145 1063.3484162896 0.0))
((0 . "LINE") (100 . "AcDbEntity") (8 . "LOUVERS") (62 . 7) (370 . 13) (100 . "AcDbLine") (10 18923.1674208145
1063.3484162896 0.0) (11 18894.0837104072 1063.3484162896 0.0))
((0 . "LINE") (100 . "AcDbEntity") (8 . "LOUVERS") (62 . 7) (370 . 13) (100 . "AcDbLine") (10 18894.0837104072
1063.3484162896 0.0) (11 18859.4230769231 1063.3484162896 0.0))
((0 . "LINE") (100 . "AcDbEntity") (8 . "LOUVERS") (62 . 7) (370 . 13) (100 . "AcDbLine") (10 18859.4230769231
1063.3484162896 0.0) (11 18818.9027149321 1063.3484162896 0.0))
((0 . "LINE") (100 . "AcDbEntity") (8 . "LOUVERS") (62 . 7) (370 . 13) (100 . "AcDbLine") (10 18818.9027149321
1063.3484162896 0.0) (11 18805.056561086 1063.3484162896 0.0))
((0 . "LINE") (100 . "AcDbEntity") (8 . "LOUVERS") (62 . 7) (370 . 13) (100 . "AcDbLine") (10 18805.056561086
1063.3484162896 0.0) (11 18762.3190045249 1063.3484162896 0.0))
((0 . "LINE") (100 . "AcDbEntity") (8 . "LOUVERS") (62 . 7) (370 . 13) (100 . "AcDbLine") (10 18762.3190045249
1063.3484162896 0.0) (11 18696.9796380091 1063.3484162896 0.0))
((0 . "LINE") (100 . "AcDbEntity") (8 . "LOUVERS") (62 . 7) (370 . 13) (100 . "AcDbLine") (10 18696.9796380091
1063.3484162896 0.0) (11 18687.7828054299 1063.3484162896 0.0))
((0 . "LINE") (100 . "AcDbEntity") (8 . "LOUVERS") (62 . 7) (370 . 13) (100 . "AcDbLine") (10 18687.7828054299
1063.3484162896 0.0) (11 18687.7828054299 2352.9411764706 0.0))
((0 . "LINE") (100 . "AcDbEntity") (8 . "LOUVERS") (62 . 7) (370 . 13) (100 . "AcDbLine") (10 18696.9796380091
2352.9411764706 0.0) (11 18696.9796380091 1063.3484162896 0.0))
((0 . "LINE") (100 . "AcDbEntity") (8 . "LOUVERS") (62 . 7) (370 . 13) (100 . "AcDbLine") (10 18762.3190045249
2352.9411764706 0.0) (11 18762.3190045249 1063.3484162896 0.0))
((0 . "LINE") (100 . "AcDbEntity") (8 . "LOUVERS") (62 . 7) (370 . 13) (100 . "AcDbLine") (10 18805.056561086
2352.9411764706 0.0) (11 18805.056561086 1063.3484162896 0.0))
((0 . "LINE") (100 . "AcDbEntity") (8 . "LOUVERS") (62 . 7) (370 . 13) (100 . "AcDbLine") (10 18818.9027149321
2352.9411764706 0.0) (11 18818.9027149321 1063.3484162896 0.0))
((0 . "LINE") (100 . "AcDbEntity") (8 . "LOUVERS") (62 . 7) (370 . 13) (100 . "AcDbLine") (10 18859.4230769231
2352.9411764706 0.0) (11 18859.4230769231 1063.3484162896 0.0))
((0 . "LINE") (100 . "AcDbEntity") (8 . "LOUVERS") (62 . 7) (370 . 13) (100 . "AcDbLine") (10 18894.0837104072
2352.9411764706 0.0) (11 18894.0837104072 1063.3484162896 0.0))
((0 . "LINE") (100 . "AcDbEntity") (8 . "LOUVERS") (62 . 7) (370 . 13) (100 . "AcDbLine") (10 18923.1674208145
2352.9411764706 0.0) (11 18923.1674208145 1063.3484162896 0.0))
((0 . "LINE") (100 . "AcDbEntity") (8 . "LOUVERS") (62 . 7) (370 . 13) (100 . "AcDbLine") (10 18962.6696832579
2352.9411764706 0.0) (11 18962.6696832579 1063.3484162896 0.0))
((0 . "LINE") (100 . "AcDbEntity") (8 . "LOUVERS") (62 . 7) (370 . 13) (100 . "AcDbLine") (10 18980.2828054299
2352.9411764706 0.0) (11 18980.2828054299 1063.3484162896 0.0))
((0 . "LINE") (100 . "AcDbEntity") (8 . "GLASS") (62 . 7) (370 . 13) (100 . "AcDbLine") (10 9242.0814479638
7024.8868778281 0.0) (11 9536.1990950226 7375.5656108597 0.0))
((0 . "LINE") (100 . "AcDbEntity") (8 . "GLASS") (62 . 7) (370 . 13) (100 . "AcDbLine") (10 9253.3936651584
6979.6380090498 0.0) (11 9536.1990950226 7296.3800904977 0.0))
((0 . "LINE") (100 . "AcDbEntity") (8 . "GLASS") (62 . 7) (370 . 13) (100 . "AcDbLine") (10 10610.8597285068
7024.8868778281 0.0) (11 10814.4796380091 7375.5656108597 0.0))
((0 . "LINE") (100 . "AcDbEntity") (8 . "GLASS") (62 . 7) (370 . 13) (100 . "AcDbLine") (10 10622.1719457014
6979.6380090498 0.0) (11 10814.4796380091 7296.3800904977 0.0))
((0 . "LINE") (100 . "AcDbEntity") (8 . "GLASS") (62 . 7) (370 . 13) (100 . "AcDbLine") (10 1572.3981900452
4615.3846153846 0.0) (11 1719.4570135747 4819.0045248869 0.0))
((0 . "LINE") (100 . "AcDbEntity") (8 . "GLASS") (62 . 7) (370 . 13) (100 . "AcDbLine") (10 1549.7737556561
4321.2669683258 0.0) (11 1719.4570135747 4581.4479638009 0.0))
((0 . "LINE") (100 . "AcDbEntity") (8 . "GLASS") (62 . 7) (370 . 13) (100 . "AcDbLine") (10 2002.2624434389
4536.1990950226 0.0) (11 2149.3212669683 4762.443438914 0.0))
((0 . "LINE") (100 . "AcDbEntity") (8 . "GLASS") (62 . 7) (370 . 13) (100 . "AcDbLine") (10 1957.0135746606
4309.9547511312 0.0) (11 2149.3212669683 4570.1357466063 0.0))
((0 . "LINE") (100 . "AcDbEntity") (8 . "GLASS") (62 . 7) (370 . 13) (100 . "AcDbLine") (10 5045.2488687783
4457.0135746606 0.0) (11 5248.8687782805 4705.8823529412 0.0))
((0 . "LINE") (100 . "AcDbEntity") (8 . "GLASS") (62 . 7) (370 . 13) (100 . "AcDbLine") (10 4966.0633484163
4162.8959276018 0.0) (11 5248.8687782805 4490.9502262443 0.0))
((0 . "LINE") (100 . "AcDbEntity") (8 . "GLASS") (62 . 7) (370 . 13) (100 . "AcDbLine") (10 5780.5429864253
4445.7013574661 0.0) (11 5972.850678733 4694.5701357466 0.0))
((0 . "LINE") (100 . "AcDbEntity") (8 . "GLASS") (62 . 7) (370 . 13) (100 . "AcDbLine") (10 5701.3574660633
4151.5837104072 0.0) (11 5972.850678733 4479.6380090498 0.0))
((0 . "LINE") (100 . "AcDbEntity") (8 . "GLASS") (62 . 7) (370 . 13) (100 . "AcDbLine") (10 8461.5384615385
4705.8823529412 0.0) (11 8597.2850678733 4909.5022624434 0.0))
((0 . "LINE") (100 . "AcDbEntity") (8 . "GLASS") (62 . 7) (370 . 13) (100 . "AcDbLine") (10 8472.850678733
4570.1357466063 0.0) (11 8631.221719457 4785.0678733032 0.0))
((0 . "LINE") (100 . "AcDbEntity") (8 . "GLASS") (62 . 7) (370 . 13) (100 . "AcDbLine") (10 8880.0904977376
4683.257918552 0.0) (11 9038.4615384615 4898.1900452489 0.0))
((0 . "LINE") (100 . "AcDbEntity") (8 . "GLASS") (62 . 7) (370 . 13) (100 . "AcDbLine") (10 8891.4027149321
4547.5113122172 0.0) (11 9061.0859728507 4762.443438914 0.0))
((0 . "LINE") (100 . "AcDbEntity") (8 . "GLASS") (62 . 7) (370 . 13) (100 . "AcDbLine") (10 8665.1583710407
3642.5339366516 0.0) (11 8959.2760180995 4004.5248868778 0.0))
((0 . "LINE") (100 . "AcDbEntity") (8 . "GLASS") (62 . 7) (370 . 13) (100 . "AcDbLine") (10 8563.3484162896
3404.9773755656 0.0) (11 8925.3393665158 3834.8416289593 0.0))
((0 . "LINE") (100 . "AcDbEntity") (8 . "GLASS") (62 . 7) (370 . 13) (100 . "AcDbLine") (10 10961.5384615385
4705.8823529412 0.0) (11 11108.5972850679 4909.5022624434 0.0))
((0 . "LINE") (100 . "AcDbEntity") (8 . "GLASS") (62 . 7) (370 . 13) (100 . "AcDbLine") (10 10961.5384615385
4570.1357466063 0.0) (11 11153.8461538462 4785.0678733032 0.0))
((0 . "LINE") (100 . "AcDbEntity") (8 . "GLASS") (62 . 7) (370 . 13) (100 . "AcDbLine") (10 11391.4027149321
4671.9457013575 0.0) (11 11527.149321267 4886.8778280543 0.0))
((0 . "LINE") (100 . "AcDbEntity") (8 . "GLASS") (62 . 7) (370 . 13) (100 . "AcDbLine") (10 11368.778280543
4536.1990950226 0.0) (11 11549.7737556561 4751.1312217195 0.0))
((0 . "LINE") (100 . "AcDbEntity") (8 . "GLASS") (62 . 7) (370 . 13) (100 . "AcDbLine") (10 11165.1583710407
3631.221719457 0.0) (11 11470.5882352941 4004.5248868778 0.0))
((0 . "LINE") (100 . "AcDbEntity") (8 . "GLASS") (62 . 7) (370 . 13) (100 . "AcDbLine") (10 11074.6606334842
3393.665158371 0.0) (11 11436.6515837104 3834.8416289593 0.0))
((0 . "LINE") (100 . "AcDbEntity") (8 . "GLASS") (62 . 7) (370 . 13) (100 . "AcDbLine") (10 8348.4162895928
1504.5248868778 0.0) (11 8597.2850678733 1877.8280542986 0.0))
((0 . "LINE") (100 . "AcDbEntity") (8 . "GLASS") (62 . 7) (370 . 13) (100 . "AcDbLine") (10 8303.1674208145
1278.2805429864 0.0) (11 8552.036199095 1662.8959276018 0.0))
((0 . "LINE") (100 . "AcDbEntity") (8 . "GLASS") (62 . 7) (370 . 13) (100 . "AcDbLine") (10 8981.9004524887
1436.6515837104 0.0) (11 9196.8325791855 1730.7692307692 0.0))
((0 . "LINE") (100 . "AcDbEntity") (8 . "GLASS") (62 . 7) (370 . 13) (100 . "AcDbLine") (10 8947.963800905
1255.6561085973 0.0) (11 9185.520361991 1583.7104072398 0.0))
((0 . "LINE") (100 . "AcDbEntity") (8 . "GLASS") (62 . 7) (370 . 13) (100 . "AcDbLine") (10 10871.0407239819
1515.8371040724 0.0) (11 11074.6606334842 1821.2669683258 0.0))
((0 . "LINE") (100 . "AcDbEntity") (8 . "GLASS") (62 . 7) (370 . 13) (100 . "AcDbLine") (10 10825.7918552036
1278.2805429864 0.0) (11 11063.3484162896 1628.9592760181 0.0))
((0 . "LINE") (100 . "AcDbEntity") (8 . "GLASS") (62 . 7) (370 . 13) (100 . "AcDbLine") (10 11470.5882352941
1459.2760180995 0.0) (11 11685.520361991 1730.7692307692 0.0))
((0 . "LINE") (100 . "AcDbEntity") (8 . "GLASS") (62 . 7) (370 . 13) (100 . "AcDbLine") (10 11425.3393665158
1266.9683257919 0.0) (11 11674.2081447964 1561.0859728507 0.0))
((0 . "LINE") (100 . "AcDbEntity") (8 . "GLASS") (62 . 7) (370 . 13) (100 . "AcDbLine") (10 5045.2488687783
1651.5837104072 0.0) (11 5260.1809954751 1945.7013574661 0.0))
((0 . "LINE") (100 . "AcDbEntity") (8 . "GLASS") (62 . 7) (370 . 13) (100 . "AcDbLine") (10 4966.0633484163
1357.4660633484 0.0) (11 5237.556561086 1685.520361991 0.0))
((0 . "LINE") (100 . "AcDbEntity") (8 . "GLASS") (62 . 7) (370 . 13) (100 . "AcDbLine") (10 5780.5429864253
1628.9592760181 0.0) (11 6006.7873303167 1934.3891402715 0.0))
((0 . "LINE") (100 . "AcDbEntity") (8 . "GLASS") (62 . 7) (370 . 13) (100 . "AcDbLine") (10 5712.6696832579
1346.1538461538 0.0) (11 5984.1628959276 1674.2081447964 0.0))
((0 . "LINE") (100 . "AcDbEntity") (8 . "GLASS") (62 . 7) (370 . 13) (100 . "AcDbLine") (10 1572.3981900452
1787.3303167421 0.0) (11 1719.4570135747 1990.9502262443 0.0))
((0 . "LINE") (100 . "AcDbEntity") (8 . "GLASS") (62 . 7) (370 . 13) (100 . "AcDbLine") (10 1549.7737556561
1493.2126696833 0.0) (11 1719.4570135747 1753.3936651584 0.0))
((0 . "LINE") (100 . "AcDbEntity") (8 . "GLASS") (62 . 7) (370 . 13) (100 . "AcDbLine") (10 2002.2624434389
1708.1447963801 0.0) (11 2149.3212669683 1934.3891402715 0.0))
((0 . "LINE") (100 . "AcDbEntity") (8 . "GLASS") (62 . 7) (370 . 13) (100 . "AcDbLine") (10 1957.0135746606
1481.9004524887 0.0) (11 2149.3212669683 1742.0814479638 0.0))
((0 . "LINE") (100 . "AcDbEntity") (8 . "GLASS") (62 . 7) (370 . 13) (100 . "AcDbLine") (10 14196.8325791855
4457.0135746606 0.0) (11 14400.4524886878 4705.8823529412 0.0))
((0 . "LINE") (100 . "AcDbEntity") (8 . "GLASS") (62 . 7) (370 . 13) (100 . "AcDbLine") (10 14117.6470588235
4162.8959276018 0.0) (11 14400.4524886878 4490.9502262443 0.0))
((0 . "LINE") (100 . "AcDbEntity") (8 . "GLASS") (62 . 7) (370 . 13) (100 . "AcDbLine") (10 14932.1266968326
4445.7013574661 0.0) (11 15124.4343891403 4694.5701357466 0.0))
((0 . "LINE") (100 . "AcDbEntity") (8 . "GLASS") (62 . 7) (370 . 13) (100 . "AcDbLine") (10 14852.9411764706
4151.5837104072 0.0) (11 15124.4343891403 4479.6380090498 0.0))
((0 . "LINE") (100 . "AcDbEntity") (8 . "GLASS") (62 . 7) (370 . 13) (100 . "AcDbLine") (10 14196.8325791855
1651.5837104072 0.0) (11 14411.7647058824 1945.7013574661 0.0))
((0 . "LINE") (100 . "AcDbEntity") (8 . "GLASS") (62 . 7) (370 . 13) (100 . "AcDbLine") (10 14117.6470588235
1357.4660633484 0.0) (11 14389.1402714932 1685.520361991 0.0))
((0 . "LINE") (100 . "AcDbEntity") (8 . "GLASS") (62 . 7) (370 . 13) (100 . "AcDbLine") (10 14932.1266968326
1628.9592760181 0.0) (11 15158.371040724 1934.3891402715 0.0))
((0 . "LINE") (100 . "AcDbEntity") (8 . "GLASS") (62 . 7) (370 . 13) (100 . "AcDbLine") (10 14864.2533936652
1346.1538461538 0.0) (11 15135.7466063348 1674.2081447964 0.0))
((0 . "LINE") (100 . "AcDbEntity") (8 . "GLASS") (62 . 7) (370 . 13) (100 . "AcDbLine") (10 17907.2398190045
4615.3846153846 0.0) (11 18054.2986425339 4819.0045248869 0.0))
((0 . "LINE") (100 . "AcDbEntity") (8 . "GLASS") (62 . 7) (370 . 13) (100 . "AcDbLine") (10 17907.2398190045
1787.3303167421 0.0) (11 18054.2986425339 1990.9502262443 0.0))
((0 . "LINE") (100 . "AcDbEntity") (8 . "GLASS") (62 . 7) (370 . 13) (100 . "AcDbLine") (10 17884.6153846154
4321.2669683258 0.0) (11 18054.2986425339 4581.4479638009 0.0))
((0 . "LINE") (100 . "AcDbEntity") (8 . "GLASS") (62 . 7) (370 . 13) (100 . "AcDbLine") (10 17884.6153846154
1493.2126696833 0.0) (11 18054.2986425339 1753.3936651584 0.0))
((0 . "LINE") (100 . "AcDbEntity") (8 . "GLASS") (62 . 7) (370 . 13) (100 . "AcDbLine") (10 18337.1040723982
4536.1990950226 0.0) (11 18484.1628959276 4762.443438914 0.0))
((0 . "LINE") (100 . "AcDbEntity") (8 . "GLASS") (62 . 7) (370 . 13) (100 . "AcDbLine") (10 18337.1040723982
1708.1447963801 0.0) (11 18484.1628959276 1934.3891402715 0.0))
((0 . "LINE") (100 . "AcDbEntity") (8 . "GLASS") (62 . 7) (370 . 13) (100 . "AcDbLine") (10 18291.8552036199
4309.9547511312 0.0) (11 18484.1628959276 4570.1357466063 0.0))
((0 . "LINE") (100 . "AcDbEntity") (8 . "GLASS") (62 . 7) (370 . 13) (100 . "AcDbLine") (10 18291.8552036199
1481.9004524887 0.0) (11 18484.1628959276 1742.0814479638 0.0))
((0 . "LINE") (100 . "AcDbEntity") (8 . "WINDOWS") (62 . 7) (370 . 13) (100 . "AcDbLine") (10 4671.9457013575
3800.9049773756 0.0) (11 4739.8190045249 3800.9049773756 0.0))
((0 . "LINE") (100 . "AcDbEntity") (8 . "WINDOWS") (62 . 7) (370 . 13) (100 . "AcDbLine") (10 4739.8190045249
3800.9049773756 0.0) (11 4785.0678733032 3800.9049773756 0.0))
((0 . "LINE") (100 . "AcDbEntity") (8 . "WINDOWS") (62 . 7) (370 . 13) (100 . "AcDbLine") (10 4785.0678733032
3800.9049773756 0.0) (11 5407.2398190045 3800.9049773756 0.0))
((0 . "LINE") (100 . "AcDbEntity") (8 . "WINDOWS") (62 . 7) (370 . 13) (100 . "AcDbLine") (10 5407.2398190045
3800.9049773756 0.0) (11 5486.4253393665 3800.9049773756 0.0))
((0 . "LINE") (100 . "AcDbEntity") (8 . "WINDOWS") (62 . 7) (370 . 13) (100 . "AcDbLine") (10 5486.4253393665
3800.9049773756 0.0) (11 6108.5972850679 3800.9049773756 0.0))
((0 . "LINE") (100 . "AcDbEntity") (8 . "WINDOWS") (62 . 7) (370 . 13) (100 . "AcDbLine") (10 6108.5972850679
3800.9049773756 0.0) (11 6153.8461538462 3800.9049773756 0.0))
((0 . "LINE") (100 . "AcDbEntity") (8 . "WINDOWS") (62 . 7) (370 . 13) (100 . "AcDbLine") (10 6153.8461538462
3800.9049773756 0.0) (11 6210.407239819 3800.9049773756 0.0))
((0 . "LINE") (100 . "AcDbEntity") (8 . "WINDOWS") (62 . 7) (370 . 13) (100 . "AcDbLine") (10 4739.8190045249 5000 0.0)
(11 4739.8190045249 3800.9049773756 0.0))
((0 . "LINE") (100 . "AcDbEntity") (8 . "WINDOWS") (62 . 7) (370 . 13) (100 . "AcDbLine") (10 6153.8461538462 5000 0.0)
(11 6153.8461538462 3800.9049773756 0.0))
((0 . "LINE") (100 . "AcDbEntity") (8 . "WINDOWS") (62 . 7) (370 . 13) (100 . "AcDbLine") (10 4785.0678733032
4966.0633484163 0.0) (11 4785.0678733032 3800.9049773756 0.0))
((0 . "LINE") (100 . "AcDbEntity") (8 . "WINDOWS") (62 . 7) (370 . 13) (100 . "AcDbLine") (10 6108.5972850679
4966.0633484163 0.0) (11 6108.5972850679 3800.9049773756 0.0))
((0 . "LINE") (100 . "AcDbEntity") (8 . "WINDOWS") (62 . 7) (370 . 13) (100 . "AcDbLine") (10 5407.2398190045
5101.3436030836 0.0) (11 5407.2398190045 3800.9049773756 0.0))
((0 . "LINE") (100 . "AcDbEntity") (8 . "WINDOWS") (62 . 7) (370 . 13) (100 . "AcDbLine") (10 5486.4253393665
5101.3436030836 0.0) (11 5486.4253393665 3800.9049773756 0.0))
((0 . "LINE") (100 . "AcDbEntity") (8 . "WINDOWS") (62 . 7) (370 . 13) (100 . "AcDbLine") (10 4660.6334841629
972.850678733 0.0) (11 4660.6334841629 950.2262443439 0.0))
((0 . "LINE") (100 . "AcDbEntity") (8 . "WINDOWS") (62 . 7) (370 . 13) (100 . "AcDbLine") (10 6210.407239819
972.850678733 0.0) (11 6210.407239819 950.2262443439 0.0))
((0 . "LINE") (100 . "AcDbEntity") (8 . "WINDOWS") (62 . 7) (370 . 13) (100 . "AcDbLine") (10 4660.6334841629
950.2262443439 0.0) (11 4728.5067873303 950.2262443439 0.0))
((0 . "LINE") (100 . "AcDbEntity") (8 . "WINDOWS") (62 . 7) (370 . 13) (100 . "AcDbLine") (10 4728.5067873303
950.2262443439 0.0) (11 4773.7556561086 950.2262443439 0.0))
((0 . "LINE") (100 . "AcDbEntity") (8 . "WINDOWS") (62 . 7) (370 . 13) (100 . "AcDbLine") (10 4773.7556561086
950.2262443439 0.0) (11 5407.2398190045 950.2262443439 0.0))
((0 . "LINE") (100 . "AcDbEntity") (8 . "WINDOWS") (62 . 7) (370 . 13) (100 . "AcDbLine") (10 5407.2398190045
950.2262443439 0.0) (11 5486.4253393665 950.2262443439 0.0))
((0 . "LINE") (100 . "AcDbEntity") (8 . "WINDOWS") (62 . 7) (370 . 13) (100 . "AcDbLine") (10 5486.4253393665
950.2262443439 0.0) (11 6108.5972850679 950.2262443439 0.0))
((0 . "LINE") (100 . "AcDbEntity") (8 . "WINDOWS") (62 . 7) (370 . 13) (100 . "AcDbLine") (10 6108.5972850679
950.2262443439 0.0) (11 6153.8461538462 950.2262443439 0.0))
((0 . "LINE") (100 . "AcDbEntity") (8 . "WINDOWS") (62 . 7) (370 . 13) (100 . "AcDbLine") (10 6153.8461538462
950.2262443439 0.0) (11 6210.407239819 950.2262443439 0.0))
((0 . "LINE") (100 . "AcDbEntity") (8 . "WINDOWS") (62 . 7) (370 . 13) (100 . "AcDbLine") (10 4728.5067873303
2149.3212669683 0.0) (11 4728.5067873303 950.2262443439 0.0))
((0 . "LINE") (100 . "AcDbEntity") (8 . "WINDOWS") (62 . 7) (370 . 13) (100 . "AcDbLine") (10 6153.8461538462
2149.3212669683 0.0) (11 6153.8461538462 950.2262443439 0.0))
((0 . "LINE") (100 . "AcDbEntity") (8 . "WINDOWS") (62 . 7) (370 . 13) (100 . "AcDbLine") (10 4773.7556561086
2104.07239819 0.0) (11 4773.7556561086 950.2262443439 0.0))
((0 . "LINE") (100 . "AcDbEntity") (8 . "WINDOWS") (62 . 7) (370 . 13) (100 . "AcDbLine") (10 6108.5972850679
2104.07239819 0.0) (11 6108.5972850679 950.2262443439 0.0))
((0 . "LINE") (100 . "AcDbEntity") (8 . "WINDOWS") (62 . 7) (370 . 13) (100 . "AcDbLine") (10 5407.2398190045
2307.2105866853 0.0) (11 5407.2398190045 950.2262443439 0.0))
((0 . "LINE") (100 . "AcDbEntity") (8 . "WINDOWS") (62 . 7) (370 . 13) (100 . "AcDbLine") (10 5486.4253393665
2306.8357805128 0.0) (11 5486.4253393665 950.2262443439 0.0))
((0 . "LINE") (100 . "AcDbEntity") (8 . "WINDOWS") (62 . 7) (370 . 13) (100 . "AcDbLine") (10 13823.5294117647
3800.9049773756 0.0) (11 13891.4027149321 3800.9049773756 0.0))
((0 . "LINE") (100 . "AcDbEntity") (8 . "WINDOWS") (62 . 7) (370 . 13) (100 . "AcDbLine") (10 13891.4027149321
3800.9049773756 0.0) (11 13936.6515837104 3800.9049773756 0.0))
((0 . "LINE") (100 . "AcDbEntity") (8 . "WINDOWS") (62 . 7) (370 . 13) (100 . "AcDbLine") (10 13936.6515837104
3800.9049773756 0.0) (11 14558.8235294118 3800.9049773756 0.0))
((0 . "LINE") (100 . "AcDbEntity") (8 . "WINDOWS") (62 . 7) (370 . 13) (100 . "AcDbLine") (10 14558.8235294118
3800.9049773756 0.0) (11 14638.0090497738 3800.9049773756 0.0))
((0 . "LINE") (100 . "AcDbEntity") (8 . "WINDOWS") (62 . 7) (370 . 13) (100 . "AcDbLine") (10 14638.0090497738
3800.9049773756 0.0) (11 15260.1809954751 3800.9049773756 0.0))
((0 . "LINE") (100 . "AcDbEntity") (8 . "WINDOWS") (62 . 7) (370 . 13) (100 . "AcDbLine") (10 15260.1809954751
3800.9049773756 0.0) (11 15305.4298642534 3800.9049773756 0.0))
((0 . "LINE") (100 . "AcDbEntity") (8 . "WINDOWS") (62 . 7) (370 . 13) (100 . "AcDbLine") (10 15305.4298642534
3800.9049773756 0.0) (11 15361.9909502262 3800.9049773756 0.0))
((0 . "LINE") (100 . "AcDbEntity") (8 . "WINDOWS") (62 . 7) (370 . 13) (100 . "AcDbLine") (10 13891.4027149321 5000 0.0)
(11 13891.4027149321 3800.9049773756 0.0))
((0 . "LINE") (100 . "AcDbEntity") (8 . "WINDOWS") (62 . 7) (370 . 13) (100 . "AcDbLine") (10 15305.4298642534 5000 0.0)
(11 15305.4298642534 3800.9049773756 0.0))
((0 . "LINE") (100 . "AcDbEntity") (8 . "WINDOWS") (62 . 7) (370 . 13) (100 . "AcDbLine") (10 13936.6515837104
4966.0633484163 0.0) (11 13936.6515837104 3800.9049773756 0.0))
((0 . "LINE") (100 . "AcDbEntity") (8 . "WINDOWS") (62 . 7) (370 . 13) (100 . "AcDbLine") (10 15260.1809954751
4966.0633484163 0.0) (11 15260.1809954751 3800.9049773756 0.0))
((0 . "LINE") (100 . "AcDbEntity") (8 . "WINDOWS") (62 . 7) (370 . 13) (100 . "AcDbLine") (10 14558.8235294118
5101.3436030836 0.0) (11 14558.8235294118 3800.9049773756 0.0))
((0 . "LINE") (100 . "AcDbEntity") (8 . "WINDOWS") (62 . 7) (370 . 13) (100 . "AcDbLine") (10 14638.0090497738
5101.3436030836 0.0) (11 14638.0090497738 3800.9049773756 0.0))
((0 . "LINE") (100 . "AcDbEntity") (8 . "WINDOWS") (62 . 7) (370 . 13) (100 . "AcDbLine") (10 13812.2171945701
972.850678733 0.0) (11 13812.2171945701 950.2262443439 0.0))
((0 . "LINE") (100 . "AcDbEntity") (8 . "WINDOWS") (62 . 7) (370 . 13) (100 . "AcDbLine") (10 15361.9909502262
972.850678733 0.0) (11 15361.9909502262 950.2262443439 0.0))
((0 . "LINE") (100 . "AcDbEntity") (8 . "WINDOWS") (62 . 7) (370 . 13) (100 . "AcDbLine") (10 13812.2171945701
950.2262443439 0.0) (11 13880.0904977376 950.2262443439 0.0))
((0 . "LINE") (100 . "AcDbEntity") (8 . "WINDOWS") (62 . 7) (370 . 13) (100 . "AcDbLine") (10 13880.0904977376
950.2262443439 0.0) (11 13925.3393665158 950.2262443439 0.0))
((0 . "LINE") (100 . "AcDbEntity") (8 . "WINDOWS") (62 . 7) (370 . 13) (100 . "AcDbLine") (10 13925.3393665158
950.2262443439 0.0) (11 14558.8235294118 950.2262443439 0.0))
((0 . "LINE") (100 . "AcDbEntity") (8 . "WINDOWS") (62 . 7) (370 . 13) (100 . "AcDbLine") (10 14558.8235294118
950.2262443439 0.0) (11 14638.0090497738 950.2262443439 0.0))
((0 . "LINE") (100 . "AcDbEntity") (8 . "WINDOWS") (62 . 7) (370 . 13) (100 . "AcDbLine") (10 14638.0090497738
950.2262443439 0.0) (11 15260.1809954751 950.2262443439 0.0))
((0 . "LINE") (100 . "AcDbEntity") (8 . "WINDOWS") (62 . 7) (370 . 13) (100 . "AcDbLine") (10 15260.1809954751
950.2262443439 0.0) (11 15305.4298642534 950.2262443439 0.0))
((0 . "LINE") (100 . "AcDbEntity") (8 . "WINDOWS") (62 . 7) (370 . 13) (100 . "AcDbLine") (10 15305.4298642534
950.2262443439 0.0) (11 15361.9909502262 950.2262443439 0.0))
((0 . "LINE") (100 . "AcDbEntity") (8 . "WINDOWS") (62 . 7) (370 . 13) (100 . "AcDbLine") (10 13880.0904977376
2149.3212669683 0.0) (11 13880.0904977376 950.2262443439 0.0))
((0 . "LINE") (100 . "AcDbEntity") (8 . "WINDOWS") (62 . 7) (370 . 13) (100 . "AcDbLine") (10 15305.4298642534
2149.3212669683 0.0) (11 15305.4298642534 950.2262443439 0.0))
((0 . "LINE") (100 . "AcDbEntity") (8 . "WINDOWS") (62 . 7) (370 . 13) (100 . "AcDbLine") (10 13925.3393665158
2104.07239819 0.0) (11 13925.3393665158 950.2262443439 0.0))
((0 . "LINE") (100 . "AcDbEntity") (8 . "WINDOWS") (62 . 7) (370 . 13) (100 . "AcDbLine") (10 15260.1809954751
2104.07239819 0.0) (11 15260.1809954751 950.2262443439 0.0))
((0 . "LINE") (100 . "AcDbEntity") (8 . "WINDOWS") (62 . 7) (370 . 13) (100 . "AcDbLine") (10 14558.8235294118
2307.2105866853 0.0) (11 14558.8235294118 950.2262443439 0.0))
((0 . "LINE") (100 . "AcDbEntity") (8 . "WINDOWS") (62 . 7) (370 . 13) (100 . "AcDbLine") (10 14638.0090497738
2306.8357805128 0.0) (11 14638.0090497738 950.2262443439 0.0))
((0 . "LINE") (100 . "AcDbEntity") (8 . "WINDOWS") (62 . 7) (370 . 13) (100 . "AcDbLine") (10 1346.1538461538
5045.2488687783 0.0) (11 1346.1538461538 3880.0904977376 0.0))
((0 . "LINE") (100 . "AcDbEntity") (8 . "WINDOWS") (62 . 7) (370 . 13) (100 . "AcDbLine") (10 2319.0045248869
5045.2488687783 0.0) (11 2319.0045248869 3880.0904977376 0.0))
((0 . "LINE") (100 . "AcDbEntity") (8 . "WINDOWS") (62 . 7) (370 . 13) (100 . "AcDbLine") (10 1346.1538461538
3880.0904977376 0.0) (11 1414.0271493213 3880.0904977376 0.0))
((0 . "LINE") (100 . "AcDbEntity") (8 . "WINDOWS") (62 . 7) (370 . 13) (100 . "AcDbLine") (10 1414.0271493213
3880.0904977376 0.0) (11 1470.5882352941 3880.0904977376 0.0))
((0 . "LINE") (100 . "AcDbEntity") (8 . "WINDOWS") (62 . 7) (370 . 13) (100 . "AcDbLine") (10 1470.5882352941
3880.0904977376 0.0) (11 1798.6425339367 3880.0904977376 0.0))
((0 . "LINE") (100 . "AcDbEntity") (8 . "WINDOWS") (62 . 7) (370 . 13) (100 . "AcDbLine") (10 1798.6425339367
3880.0904977376 0.0) (11 1866.5158371041 3880.0904977376 0.0))
((0 . "LINE") (100 . "AcDbEntity") (8 . "WINDOWS") (62 . 7) (370 . 13) (100 . "AcDbLine") (10 1866.5158371041
3880.0904977376 0.0) (11 2194.5701357466 3880.0904977376 0.0))
((0 . "LINE") (100 . "AcDbEntity") (8 . "WINDOWS") (62 . 7) (370 . 13) (100 . "AcDbLine") (10 2194.5701357466
3880.0904977376 0.0) (11 2251.1312217195 3880.0904977376 0.0))
((0 . "LINE") (100 . "AcDbEntity") (8 . "WINDOWS") (62 . 7) (370 . 13) (100 . "AcDbLine") (10 2251.1312217195
3880.0904977376 0.0) (11 2319.0045248869 3880.0904977376 0.0))
((0 . "LINE") (100 . "AcDbEntity") (8 . "WINDOWS") (62 . 7) (370 . 13) (100 . "AcDbLine") (10 1414.0271493213
5011.3122171946 0.0) (11 1414.0271493213 3880.0904977376 0.0))
((0 . "LINE") (100 . "AcDbEntity") (8 . "WINDOWS") (62 . 7) (370 . 13) (100 . "AcDbLine") (10 2251.1312217195
5011.3122171946 0.0) (11 2251.1312217195 3880.0904977376 0.0))
((0 . "LINE") (100 . "AcDbEntity") (8 . "WINDOWS") (62 . 7) (370 . 13) (100 . "AcDbLine") (10 1470.5882352941
4966.0633484163 0.0) (11 1470.5882352941 3880.0904977376 0.0))
((0 . "LINE") (100 . "AcDbEntity") (8 . "WINDOWS") (62 . 7) (370 . 13) (100 . "AcDbLine") (10 2194.5701357466
4966.0633484163 0.0) (11 2194.5701357466 3880.0904977376 0.0))
((0 . "LINE") (100 . "AcDbEntity") (8 . "WINDOWS") (62 . 7) (370 . 13) (100 . "AcDbLine") (10 1798.6425339367
5112.011571045 0.0) (11 1798.6425339367 3880.0904977376 0.0))
((0 . "LINE") (100 . "AcDbEntity") (8 . "WINDOWS") (62 . 7) (370 . 13) (100 . "AcDbLine") (10 1866.5158371041
5112.011571045 0.0) (11 1866.5158371041 3880.0904977376 0.0))
((0 . "LINE") (100 . "AcDbEntity") (8 . "WINDOWS") (62 . 7) (370 . 13) (100 . "AcDbLine") (10 1742.0814479638
5441.1764705882 0.0) (11 1923.0769230769 5441.1764705882 0.0))
((0 . "LINE") (100 . "AcDbEntity") (8 . "WINDOWS") (62 . 7) (370 . 13) (100 . "AcDbLine") (10 1923.0769230769
5441.1764705882 0.0) (11 1900.4051368801 5312.703015473 0.0))
((0 . "LINE") (100 . "AcDbEntity") (8 . "WINDOWS") (62 . 7) (370 . 13) (100 . "AcDbLine") (10 1900.4051368801
5312.703015473 0.0) (11 1889.1402714932 5248.8687782805 0.0))
((0 . "LINE") (100 . "AcDbEntity") (8 . "WINDOWS") (62 . 7) (370 . 13) (100 . "AcDbLine") (10 1889.1402714932
5248.8687782805 0.0) (11 1776.0180995475 5248.8687782805 0.0))
((0 . "LINE") (100 . "AcDbEntity") (8 . "WINDOWS") (62 . 7) (370 . 13) (100 . "AcDbLine") (10 1776.0180995475
5248.8687782805 0.0) (11 1764.7532341606 5312.703015473 0.0))
((0 . "LINE") (100 . "AcDbEntity") (8 . "WINDOWS") (62 . 7) (370 . 13) (100 . "AcDbLine") (10 1764.7532341606
5312.703015473 0.0) (11 1742.0814479638 5441.1764705882 0.0))
((0 . "LINE") (100 . "AcDbEntity") (8 . "WINDOWS") (62 . 7) (370 . 13) (100 . "AcDbLine") (10 1346.1538461538
2217.1945701357 0.0) (11 1346.1538461538 1052.036199095 0.0))
((0 . "LINE") (100 . "AcDbEntity") (8 . "WINDOWS") (62 . 7) (370 . 13) (100 . "AcDbLine") (10 2319.0045248869
2217.1945701357 0.0) (11 2319.0045248869 1052.036199095 0.0))
((0 . "LINE") (100 . "AcDbEntity") (8 . "WINDOWS") (62 . 7) (370 . 13) (100 . "AcDbLine") (10 1346.1538461538
1052.036199095 0.0) (11 1414.0271493213 1052.036199095 0.0))
((0 . "LINE") (100 . "AcDbEntity") (8 . "WINDOWS") (62 . 7) (370 . 13) (100 . "AcDbLine") (10 1414.0271493213
1052.036199095 0.0) (11 1470.5882352941 1052.036199095 0.0))
((0 . "LINE") (100 . "AcDbEntity") (8 . "WINDOWS") (62 . 7) (370 . 13) (100 . "AcDbLine") (10 1470.5882352941
1052.036199095 0.0) (11 1798.6425339367 1052.036199095 0.0))
((0 . "LINE") (100 . "AcDbEntity") (8 . "WINDOWS") (62 . 7) (370 . 13) (100 . "AcDbLine") (10 1798.6425339367
1052.036199095 0.0) (11 1866.5158371041 1052.036199095 0.0))
((0 . "LINE") (100 . "AcDbEntity") (8 . "WINDOWS") (62 . 7) (370 . 13) (100 . "AcDbLine") (10 1866.5158371041
1052.036199095 0.0) (11 2194.5701357466 1052.036199095 0.0))
((0 . "LINE") (100 . "AcDbEntity") (8 . "WINDOWS") (62 . 7) (370 . 13) (100 . "AcDbLine") (10 2194.5701357466
1052.036199095 0.0) (11 2251.1312217195 1052.036199095 0.0))
((0 . "LINE") (100 . "AcDbEntity") (8 . "WINDOWS") (62 . 7) (370 . 13) (100 . "AcDbLine") (10 2251.1312217195
1052.036199095 0.0) (11 2319.0045248869 1052.036199095 0.0))
((0 . "LINE") (100 . "AcDbEntity") (8 . "WINDOWS") (62 . 7) (370 . 13) (100 . "AcDbLine") (10 1414.0271493213
2183.257918552 0.0) (11 1414.0271493213 1052.036199095 0.0))
((0 . "LINE") (100 . "AcDbEntity") (8 . "WINDOWS") (62 . 7) (370 . 13) (100 . "AcDbLine") (10 2251.1312217195
2183.257918552 0.0) (11 2251.1312217195 1052.036199095 0.0))
((0 . "LINE") (100 . "AcDbEntity") (8 . "WINDOWS") (62 . 7) (370 . 13) (100 . "AcDbLine") (10 1470.5882352941
2138.0090497738 0.0) (11 1470.5882352941 1052.036199095 0.0))
((0 . "LINE") (100 . "AcDbEntity") (8 . "WINDOWS") (62 . 7) (370 . 13) (100 . "AcDbLine") (10 2194.5701357466
2138.0090497738 0.0) (11 2194.5701357466 1052.036199095 0.0))
((0 . "LINE") (100 . "AcDbEntity") (8 . "WINDOWS") (62 . 7) (370 . 13) (100 . "AcDbLine") (10 1798.6425339367
2283.9572724025 0.0) (11 1798.6425339367 1052.036199095 0.0))
((0 . "LINE") (100 . "AcDbEntity") (8 . "WINDOWS") (62 . 7) (370 . 13) (100 . "AcDbLine") (10 1866.5158371041
2283.9572724025 0.0) (11 1866.5158371041 1052.036199095 0.0))
((0 . "LINE") (100 . "AcDbEntity") (8 . "WINDOWS") (62 . 7) (370 . 13) (100 . "AcDbLine") (10 1742.0814479638
2613.1221719457 0.0) (11 1923.0769230769 2613.1221719457 0.0))
((0 . "LINE") (100 . "AcDbEntity") (8 . "WINDOWS") (62 . 7) (370 . 13) (100 . "AcDbLine") (10 1923.0769230769
2613.1221719457 0.0) (11 1900.4051368801 2484.6487168304 0.0))
((0 . "LINE") (100 . "AcDbEntity") (8 . "WINDOWS") (62 . 7) (370 . 13) (100 . "AcDbLine") (10 1900.4051368801
2484.6487168304 0.0) (11 1889.1402714932 2420.814479638 0.0))
((0 . "LINE") (100 . "AcDbEntity") (8 . "WINDOWS") (62 . 7) (370 . 13) (100 . "AcDbLine") (10 1889.1402714932
2420.814479638 0.0) (11 1776.0180995475 2420.814479638 0.0))
((0 . "LINE") (100 . "AcDbEntity") (8 . "WINDOWS") (62 . 7) (370 . 13) (100 . "AcDbLine") (10 1776.0180995475
2420.814479638 0.0) (11 1764.7532341606 2484.6487168304 0.0))
((0 . "LINE") (100 . "AcDbEntity") (8 . "WINDOWS") (62 . 7) (370 . 13) (100 . "AcDbLine") (10 1764.7532341606
2484.6487168304 0.0) (11 1742.0814479638 2613.1221719457 0.0))
((0 . "LINE") (100 . "AcDbEntity") (8 . "WINDOWS") (62 . 7) (370 . 13) (100 . "AcDbLine") (10 17680.9954751131
5045.2488687783 0.0) (11 17680.9954751131 3880.0904977376 0.0))
((0 . "LINE") (100 . "AcDbEntity") (8 . "WINDOWS") (62 . 7) (370 . 13) (100 . "AcDbLine") (10 18653.8461538462
5045.2488687783 0.0) (11 18653.8461538462 3880.0904977376 0.0))
((0 . "LINE") (100 . "AcDbEntity") (8 . "WINDOWS") (62 . 7) (370 . 13) (100 . "AcDbLine") (10 17680.9954751131
3880.0904977376 0.0) (11 17748.8687782805 3880.0904977376 0.0))
((0 . "LINE") (100 . "AcDbEntity") (8 . "WINDOWS") (62 . 7) (370 . 13) (100 . "AcDbLine") (10 17748.8687782805
3880.0904977376 0.0) (11 17805.4298642534 3880.0904977376 0.0))
((0 . "LINE") (100 . "AcDbEntity") (8 . "WINDOWS") (62 . 7) (370 . 13) (100 . "AcDbLine") (10 17805.4298642534
3880.0904977376 0.0) (11 18133.4841628959 3880.0904977376 0.0))
((0 . "LINE") (100 . "AcDbEntity") (8 . "WINDOWS") (62 . 7) (370 . 13) (100 . "AcDbLine") (10 18133.4841628959
3880.0904977376 0.0) (11 18201.3574660633 3880.0904977376 0.0))
((0 . "LINE") (100 . "AcDbEntity") (8 . "WINDOWS") (62 . 7) (370 . 13) (100 . "AcDbLine") (10 18201.3574660633
3880.0904977376 0.0) (11 18529.4117647059 3880.0904977376 0.0))
((0 . "LINE") (100 . "AcDbEntity") (8 . "WINDOWS") (62 . 7) (370 . 13) (100 . "AcDbLine") (10 18529.4117647059
3880.0904977376 0.0) (11 18585.9728506787 3880.0904977376 0.0))
((0 . "LINE") (100 . "AcDbEntity") (8 . "WINDOWS") (62 . 7) (370 . 13) (100 . "AcDbLine") (10 18585.9728506787
3880.0904977376 0.0) (11 18653.8461538462 3880.0904977376 0.0))
((0 . "LINE") (100 . "AcDbEntity") (8 . "WINDOWS") (62 . 7) (370 . 13) (100 . "AcDbLine") (10 17748.8687782805
5011.3122171946 0.0) (11 17748.8687782805 3880.0904977376 0.0))
((0 . "LINE") (100 . "AcDbEntity") (8 . "WINDOWS") (62 . 7) (370 . 13) (100 . "AcDbLine") (10 18585.9728506787
5011.3122171946 0.0) (11 18585.9728506787 3880.0904977376 0.0))
((0 . "LINE") (100 . "AcDbEntity") (8 . "WINDOWS") (62 . 7) (370 . 13) (100 . "AcDbLine") (10 17805.4298642534
4966.0633484163 0.0) (11 17805.4298642534 3880.0904977376 0.0))
((0 . "LINE") (100 . "AcDbEntity") (8 . "WINDOWS") (62 . 7) (370 . 13) (100 . "AcDbLine") (10 18529.4117647059
4966.0633484163 0.0) (11 18529.4117647059 3880.0904977376 0.0))
((0 . "LINE") (100 . "AcDbEntity") (8 . "WINDOWS") (62 . 7) (370 . 13) (100 . "AcDbLine") (10 18133.4841628959
5112.011571045 0.0) (11 18133.4841628959 3880.0904977376 0.0))
((0 . "LINE") (100 . "AcDbEntity") (8 . "WINDOWS") (62 . 7) (370 . 13) (100 . "AcDbLine") (10 18201.3574660633
5112.011571045 0.0) (11 18201.3574660633 3880.0904977376 0.0))
((0 . "LINE") (100 . "AcDbEntity") (8 . "WINDOWS") (62 . 7) (370 . 13) (100 . "AcDbLine") (10 18076.9230769231
5441.1764705882 0.0) (11 18257.9185520362 5441.1764705882 0.0))
((0 . "LINE") (100 . "AcDbEntity") (8 . "WINDOWS") (62 . 7) (370 . 13) (100 . "AcDbLine") (10 18257.9185520362
5441.1764705882 0.0) (11 18235.2467658394 5312.703015473 0.0))
((0 . "LINE") (100 . "AcDbEntity") (8 . "WINDOWS") (62 . 7) (370 . 13) (100 . "AcDbLine") (10 18235.2467658394
5312.703015473 0.0) (11 18223.9819004525 5248.8687782805 0.0))
((0 . "LINE") (100 . "AcDbEntity") (8 . "WINDOWS") (62 . 7) (370 . 13) (100 . "AcDbLine") (10 18223.9819004525
5248.8687782805 0.0) (11 18110.8597285068 5248.8687782805 0.0))
((0 . "LINE") (100 . "AcDbEntity") (8 . "WINDOWS") (62 . 7) (370 . 13) (100 . "AcDbLine") (10 18110.8597285068
5248.8687782805 0.0) (11 18099.5948631199 5312.703015473 0.0))
((0 . "LINE") (100 . "AcDbEntity") (8 . "WINDOWS") (62 . 7) (370 . 13) (100 . "AcDbLine") (10 18099.5948631199
5312.703015473 0.0) (11 18076.9230769231 5441.1764705882 0.0))
((0 . "LINE") (100 . "AcDbEntity") (8 . "WINDOWS") (62 . 7) (370 . 13) (100 . "AcDbLine") (10 17680.9954751131
2217.1945701357 0.0) (11 17680.9954751131 1052.036199095 0.0))
((0 . "LINE") (100 . "AcDbEntity") (8 . "WINDOWS") (62 . 7) (370 . 13) (100 . "AcDbLine") (10 18653.8461538462
2217.1945701357 0.0) (11 18653.8461538462 1052.036199095 0.0))
((0 . "LINE") (100 . "AcDbEntity") (8 . "WINDOWS") (62 . 7) (370 . 13) (100 . "AcDbLine") (10 17680.9954751131
1052.036199095 0.0) (11 17748.8687782805 1052.036199095 0.0))
((0 . "LINE") (100 . "AcDbEntity") (8 . "WINDOWS") (62 . 7) (370 . 13) (100 . "AcDbLine") (10 17748.8687782805
1052.036199095 0.0) (11 17805.4298642534 1052.036199095 0.0))
((0 . "LINE") (100 . "AcDbEntity") (8 . "WINDOWS") (62 . 7) (370 . 13) (100 . "AcDbLine") (10 17805.4298642534
1052.036199095 0.0) (11 18133.4841628959 1052.036199095 0.0))
((0 . "LINE") (100 . "AcDbEntity") (8 . "WINDOWS") (62 . 7) (370 . 13) (100 . "AcDbLine") (10 18133.4841628959
1052.036199095 0.0) (11 18201.3574660633 1052.036199095 0.0))
((0 . "LINE") (100 . "AcDbEntity") (8 . "WINDOWS") (62 . 7) (370 . 13) (100 . "AcDbLine") (10 18201.3574660633
1052.036199095 0.0) (11 18529.4117647059 1052.036199095 0.0))
((0 . "LINE") (100 . "AcDbEntity") (8 . "WINDOWS") (62 . 7) (370 . 13) (100 . "AcDbLine") (10 18529.4117647059
1052.036199095 0.0) (11 18585.9728506787 1052.036199095 0.0))
((0 . "LINE") (100 . "AcDbEntity") (8 . "WINDOWS") (62 . 7) (370 . 13) (100 . "AcDbLine") (10 18585.9728506787
1052.036199095 0.0) (11 18653.8461538462 1052.036199095 0.0))
((0 . "LINE") (100 . "AcDbEntity") (8 . "WINDOWS") (62 . 7) (370 . 13) (100 . "AcDbLine") (10 17748.8687782805
2183.257918552 0.0) (11 17748.8687782805 1052.036199095 0.0))
((0 . "LINE") (100 . "AcDbEntity") (8 . "WINDOWS") (62 . 7) (370 . 13) (100 . "AcDbLine") (10 18585.9728506787
2183.257918552 0.0) (11 18585.9728506787 1052.036199095 0.0))
((0 . "LINE") (100 . "AcDbEntity") (8 . "WINDOWS") (62 . 7) (370 . 13) (100 . "AcDbLine") (10 17805.4298642534
2138.0090497738 0.0) (11 17805.4298642534 1052.036199095 0.0))
((0 . "LINE") (100 . "AcDbEntity") (8 . "WINDOWS") (62 . 7) (370 . 13) (100 . "AcDbLine") (10 18529.4117647059
2138.0090497738 0.0) (11 18529.4117647059 1052.036199095 0.0))
((0 . "LINE") (100 . "AcDbEntity") (8 . "WINDOWS") (62 . 7) (370 . 13) (100 . "AcDbLine") (10 18133.4841628959
2283.9572724025 0.0) (11 18133.4841628959 1052.036199095 0.0))
((0 . "LINE") (100 . "AcDbEntity") (8 . "WINDOWS") (62 . 7) (370 . 13) (100 . "AcDbLine") (10 18201.3574660633
2283.9572724025 0.0) (11 18201.3574660633 1052.036199095 0.0))
((0 . "LINE") (100 . "AcDbEntity") (8 . "WINDOWS") (62 . 7) (370 . 13) (100 . "AcDbLine") (10 18076.9230769231
2613.1221719457 0.0) (11 18257.9185520362 2613.1221719457 0.0))
((0 . "LINE") (100 . "AcDbEntity") (8 . "WINDOWS") (62 . 7) (370 . 13) (100 . "AcDbLine") (10 18257.9185520362
2613.1221719457 0.0) (11 18235.2467658394 2484.6487168304 0.0))
((0 . "LINE") (100 . "AcDbEntity") (8 . "WINDOWS") (62 . 7) (370 . 13) (100 . "AcDbLine") (10 18235.2467658394
2484.6487168304 0.0) (11 18223.9819004525 2420.814479638 0.0))
((0 . "LINE") (100 . "AcDbEntity") (8 . "WINDOWS") (62 . 7) (370 . 13) (100 . "AcDbLine") (10 18223.9819004525
2420.814479638 0.0) (11 18110.8597285068 2420.814479638 0.0))
((0 . "LINE") (100 . "AcDbEntity") (8 . "WINDOWS") (62 . 7) (370 . 13) (100 . "AcDbLine") (10 18110.8597285068
2420.814479638 0.0) (11 18099.5948631199 2484.6487168304 0.0))
((0 . "LINE") (100 . "AcDbEntity") (8 . "WINDOWS") (62 . 7) (370 . 13) (100 . "AcDbLine") (10 18099.5948631199
2484.6487168304 0.0) (11 18076.9230769231 2613.1221719457 0.0))
((0 . "LINE") (100 . "AcDbEntity") (8 . "WINDOWS") (62 . 7) (370 . 13) (100 . "AcDbLine") (10 8212.6696832579
5113.1221719457 0.0) (11 8212.6696832579 4909.5022624434 0.0))
((0 . "LINE") (100 . "AcDbEntity") (8 . "WINDOWS") (62 . 7) (370 . 13) (100 . "AcDbLine") (10 8212.6696832579
4909.5022624434 0.0) (11 8212.6696832579 3280.5429864253 0.0))
((0 . "LINE") (100 . "AcDbEntity") (8 . "WINDOWS") (62 . 7) (370 . 13) (100 . "AcDbLine") (10 9298.6425339367
5113.1221719457 0.0) (11 9298.6425339367 4909.5022624434 0.0))
((0 . "LINE") (100 . "AcDbEntity") (8 . "WINDOWS") (62 . 7) (370 . 13) (100 . "AcDbLine") (10 9298.6425339367
4909.5022624434 0.0) (11 9298.6425339367 3280.5429864253 0.0))
((0 . "LINE") (100 . "AcDbEntity") (8 . "WINDOWS") (62 . 7) (370 . 13) (100 . "AcDbLine") (10 8212.6696832579
3280.5429864253 0.0) (11 8303.1674208145 3280.5429864253 0.0))
((0 . "LINE") (100 . "AcDbEntity") (8 . "WINDOWS") (62 . 7) (370 . 13) (100 . "AcDbLine") (10 8303.1674208145
3280.5429864253 0.0) (11 8348.4162895928 3280.5429864253 0.0))
((0 . "LINE") (100 . "AcDbEntity") (8 . "WINDOWS") (62 . 7) (370 . 13) (100 . "AcDbLine") (10 8348.4162895928
3280.5429864253 0.0) (11 9162.8959276018 3280.5429864253 0.0))
((0 . "LINE") (100 . "AcDbEntity") (8 . "WINDOWS") (62 . 7) (370 . 13) (100 . "AcDbLine") (10 9162.8959276018
3280.5429864253 0.0) (11 9208.1447963801 3280.5429864253 0.0))
((0 . "LINE") (100 . "AcDbEntity") (8 . "WINDOWS") (62 . 7) (370 . 13) (100 . "AcDbLine") (10 9208.1447963801
3280.5429864253 0.0) (11 9298.6425339367 3280.5429864253 0.0))
((0 . "LINE") (100 . "AcDbEntity") (8 . "WINDOWS") (62 . 7) (370 . 13) (100 . "AcDbLine") (10 8303.1674208145
5067.8733031674 0.0) (11 8303.1674208145 3280.5429864253 0.0))
((0 . "LINE") (100 . "AcDbEntity") (8 . "WINDOWS") (62 . 7) (370 . 13) (100 . "AcDbLine") (10 9208.1447963801
5067.8733031674 0.0) (11 9208.1447963801 3280.5429864253 0.0))
((0 . "LINE") (100 . "AcDbEntity") (8 . "WINDOWS") (62 . 7) (370 . 13) (100 . "AcDbLine") (10 8348.4162895928
5022.6244343891 0.0) (11 8348.4162895928 4389.1402714932 0.0))
((0 . "LINE") (100 . "AcDbEntity") (8 . "WINDOWS") (62 . 7) (370 . 13) (100 . "AcDbLine") (10 8348.4162895928
4389.1402714932 0.0) (11 8348.4162895928 3280.5429864253 0.0))
((0 . "LINE") (100 . "AcDbEntity") (8 . "WINDOWS") (62 . 7) (370 . 13) (100 . "AcDbLine") (10 9162.8959276018
5022.6244343891 0.0) (11 9162.8959276018 4389.1402714932 0.0))
((0 . "LINE") (100 . "AcDbEntity") (8 . "WINDOWS") (62 . 7) (370 . 13) (100 . "AcDbLine") (10 9162.8959276018
4389.1402714932 0.0) (11 9162.8959276018 3280.5429864253 0.0))
((0 . "LINE") (100 . "AcDbEntity") (8 . "WINDOWS") (62 . 7) (370 . 13) (100 . "AcDbLine") (10 8721.7194570136
5213.8390258257 0.0) (11 8721.7194570136 4389.1402714932 0.0))
((0 . "LINE") (100 . "AcDbEntity") (8 . "WINDOWS") (62 . 7) (370 . 13) (100 . "AcDbLine") (10 8789.592760181
5213.8390258257 0.0) (11 8789.592760181 4389.1402714932 0.0))
((0 . "LINE") (100 . "AcDbEntity") (8 . "WINDOWS") (62 . 7) (370 . 13) (100 . "AcDbLine") (10 8348.4162895928
4389.1402714932 0.0) (11 8721.7194570136 4389.1402714932 0.0))
((0 . "LINE") (100 . "AcDbEntity") (8 . "WINDOWS") (62 . 7) (370 . 13) (100 . "AcDbLine") (10 8721.7194570136
4389.1402714932 0.0) (11 8789.592760181 4389.1402714932 0.0))
((0 . "LINE") (100 . "AcDbEntity") (8 . "WINDOWS") (62 . 7) (370 . 13) (100 . "AcDbLine") (10 8789.592760181
4389.1402714932 0.0) (11 9162.8959276018 4389.1402714932 0.0))
((0 . "LINE") (100 . "AcDbEntity") (8 . "WINDOWS") (62 . 7) (370 . 13) (100 . "AcDbLine") (10 8404.9773755656
4276.0180995475 0.0) (11 9106.334841629 4276.0180995475 0.0))
((0 . "LINE") (100 . "AcDbEntity") (8 . "WINDOWS") (62 . 7) (370 . 13) (100 . "AcDbLine") (10 9106.334841629
4276.0180995475 0.0) (11 9106.334841629 3337.1040723982 0.0))
((0 . "LINE") (100 . "AcDbEntity") (8 . "WINDOWS") (62 . 7) (370 . 13) (100 . "AcDbLine") (10 9106.334841629
3337.1040723982 0.0) (11 8404.9773755656 3337.1040723982 0.0))
((0 . "LINE") (100 . "AcDbEntity") (8 . "WINDOWS") (62 . 7) (370 . 13) (100 . "AcDbLine") (10 8404.9773755656
3337.1040723982 0.0) (11 8404.9773755656 4276.0180995475 0.0))
((0 . "LINE") (100 . "AcDbEntity") (8 . "WINDOWS") (62 . 7) (370 . 13) (100 . "AcDbLine") (10 8371.0407239819
4321.2669683258 0.0) (11 9140.2714932127 4321.2669683258 0.0))
((0 . "LINE") (100 . "AcDbEntity") (8 . "WINDOWS") (62 . 7) (370 . 13) (100 . "AcDbLine") (10 9140.2714932127
4321.2669683258 0.0) (11 9140.2714932127 3291.8552036199 0.0))
((0 . "LINE") (100 . "AcDbEntity") (8 . "WINDOWS") (62 . 7) (370 . 13) (100 . "AcDbLine") (10 9140.2714932127
3291.8552036199 0.0) (11 8371.0407239819 3291.8552036199 0.0))
((0 . "LINE") (100 . "AcDbEntity") (8 . "WINDOWS") (62 . 7) (370 . 13) (100 . "AcDbLine") (10 8371.0407239819
3291.8552036199 0.0) (11 8371.0407239819 4321.2669683258 0.0))
((0 . "LINE") (100 . "AcDbEntity") (8 . "WINDOWS") (62 . 7) (370 . 13) (100 . "AcDbLine") (10 7963.8009049774
2058.8235294118 0.0) (11 7963.8009049774 192.3076923077 0.0))
((0 . "LINE") (100 . "AcDbEntity") (8 . "WINDOWS") (62 . 7) (370 . 13) (100 . "AcDbLine") (10 7963.8009049774
192.3076923077 0.0) (11 8042.9864253394 192.3076923077 0.0))
((0 . "LINE") (100 . "AcDbEntity") (8 . "WINDOWS") (62 . 7) (370 . 13) (100 . "AcDbLine") (10 8042.9864253394
192.3076923077 0.0) (11 8099.5475113122 192.3076923077 0.0))
((0 . "LINE") (100 . "AcDbEntity") (8 . "WINDOWS") (62 . 7) (370 . 13) (100 . "AcDbLine") (10 8099.5475113122
192.3076923077 0.0) (11 8710.407239819 192.3076923077 0.0))
((0 . "LINE") (100 . "AcDbEntity") (8 . "WINDOWS") (62 . 7) (370 . 13) (100 . "AcDbLine") (10 8710.407239819
192.3076923077 0.0) (11 8800.9049773756 192.3076923077 0.0))
((0 . "LINE") (100 . "AcDbEntity") (8 . "WINDOWS") (62 . 7) (370 . 13) (100 . "AcDbLine") (10 8800.9049773756
192.3076923077 0.0) (11 9411.7647058824 192.3076923077 0.0))
((0 . "LINE") (100 . "AcDbEntity") (8 . "WINDOWS") (62 . 7) (370 . 13) (100 . "AcDbLine") (10 9411.7647058824
192.3076923077 0.0) (11 9468.3257918552 192.3076923077 0.0))
((0 . "LINE") (100 . "AcDbEntity") (8 . "WINDOWS") (62 . 7) (370 . 13) (100 . "AcDbLine") (10 9468.3257918552
192.3076923077 0.0) (11 9547.5113122172 192.3076923077 0.0))
((0 . "LINE") (100 . "AcDbEntity") (8 . "WINDOWS") (62 . 7) (370 . 13) (100 . "AcDbLine") (10 8042.9864253394
2024.8868778281 0.0) (11 8042.9864253394 192.3076923077 0.0))
((0 . "LINE") (100 . "AcDbEntity") (8 . "WINDOWS") (62 . 7) (370 . 13) (100 . "AcDbLine") (10 9468.3257918552
2024.8868778281 0.0) (11 9468.3257918552 192.3076923077 0.0))
((0 . "LINE") (100 . "AcDbEntity") (8 . "WINDOWS") (62 . 7) (370 . 13) (100 . "AcDbLine") (10 8099.5475113122
1979.6380090498 0.0) (11 8099.5475113122 984.1628959276 0.0))
((0 . "LINE") (100 . "AcDbEntity") (8 . "WINDOWS") (62 . 7) (370 . 13) (100 . "AcDbLine") (10 8099.5475113122
984.1628959276 0.0) (11 8099.5475113122 904.9773755656 0.0))
((0 . "LINE") (100 . "AcDbEntity") (8 . "WINDOWS") (62 . 7) (370 . 13) (100 . "AcDbLine") (10 8099.5475113122
904.9773755656 0.0) (11 8099.5475113122 192.3076923077 0.0))
((0 . "LINE") (100 . "AcDbEntity") (8 . "WINDOWS") (62 . 7) (370 . 13) (100 . "AcDbLine") (10 9411.7647058824
1979.6380090498 0.0) (11 9411.7647058824 984.1628959276 0.0))
((0 . "LINE") (100 . "AcDbEntity") (8 . "WINDOWS") (62 . 7) (370 . 13) (100 . "AcDbLine") (10 9411.7647058824
984.1628959276 0.0) (11 9411.7647058824 904.9773755656 0.0))
((0 . "LINE") (100 . "AcDbEntity") (8 . "WINDOWS") (62 . 7) (370 . 13) (100 . "AcDbLine") (10 9411.7647058824
904.9773755656 0.0) (11 9411.7647058824 192.3076923077 0.0))
((0 . "LINE") (100 . "AcDbEntity") (8 . "WINDOWS") (62 . 7) (370 . 13) (100 . "AcDbLine") (10 8710.407239819
2227.4714479638 0.0) (11 8710.407239819 984.1628959276 0.0))
((0 . "LINE") (100 . "AcDbEntity") (8 . "WINDOWS") (62 . 7) (370 . 13) (100 . "AcDbLine") (10 8710.407239819
984.1628959276 0.0) (11 8710.407239819 904.9773755656 0.0))
((0 . "LINE") (100 . "AcDbEntity") (8 . "WINDOWS") (62 . 7) (370 . 13) (100 . "AcDbLine") (10 8710.407239819
904.9773755656 0.0) (11 8710.407239819 192.3076923077 0.0))
((0 . "LINE") (100 . "AcDbEntity") (8 . "WINDOWS") (62 . 7) (370 . 13) (100 . "AcDbLine") (10 8800.9049773756
2227.4714479638 0.0) (11 8800.9049773756 984.1628959276 0.0))
((0 . "LINE") (100 . "AcDbEntity") (8 . "WINDOWS") (62 . 7) (370 . 13) (100 . "AcDbLine") (10 8800.9049773756
984.1628959276 0.0) (11 8800.9049773756 904.9773755656 0.0))
((0 . "LINE") (100 . "AcDbEntity") (8 . "WINDOWS") (62 . 7) (370 . 13) (100 . "AcDbLine") (10 8800.9049773756
904.9773755656 0.0) (11 8800.9049773756 192.3076923077 0.0))
((0 . "LINE") (100 . "AcDbEntity") (8 . "WINDOWS") (62 . 7) (370 . 13) (100 . "AcDbLine") (10 8099.5475113122
984.1628959276 0.0) (11 8710.407239819 984.1628959276 0.0))
((0 . "LINE") (100 . "AcDbEntity") (8 . "WINDOWS") (62 . 7) (370 . 13) (100 . "AcDbLine") (10 8710.407239819
984.1628959276 0.0) (11 8800.9049773756 984.1628959276 0.0))
((0 . "LINE") (100 . "AcDbEntity") (8 . "WINDOWS") (62 . 7) (370 . 13) (100 . "AcDbLine") (10 8800.9049773756
984.1628959276 0.0) (11 9411.7647058824 984.1628959276 0.0))
((0 . "LINE") (100 . "AcDbEntity") (8 . "WINDOWS") (62 . 7) (370 . 13) (100 . "AcDbLine") (10 8099.5475113122
904.9773755656 0.0) (11 8710.407239819 904.9773755656 0.0))
((0 . "LINE") (100 . "AcDbEntity") (8 . "WINDOWS") (62 . 7) (370 . 13) (100 . "AcDbLine") (10 8710.407239819
904.9773755656 0.0) (11 8800.9049773756 904.9773755656 0.0))
((0 . "LINE") (100 . "AcDbEntity") (8 . "WINDOWS") (62 . 7) (370 . 13) (100 . "AcDbLine") (10 8800.9049773756
904.9773755656 0.0) (11 9411.7647058824 904.9773755656 0.0))
((0 . "LINE") (100 . "AcDbEntity") (8 . "WINDOWS") (62 . 7) (370 . 13) (100 . "AcDbLine") (10 8201.3574660633
791.8552036199 0.0) (11 8540.7239819005 791.8552036199 0.0))
((0 . "LINE") (100 . "AcDbEntity") (8 . "WINDOWS") (62 . 7) (370 . 13) (100 . "AcDbLine") (10 8540.7239819005
791.8552036199 0.0) (11 8540.7239819005 305.4298642534 0.0))
((0 . "LINE") (100 . "AcDbEntity") (8 . "WINDOWS") (62 . 7) (370 . 13) (100 . "AcDbLine") (10 8540.7239819005
305.4298642534 0.0) (11 8201.3574660633 305.4298642534 0.0))
((0 . "LINE") (100 . "AcDbEntity") (8 . "WINDOWS") (62 . 7) (370 . 13) (100 . "AcDbLine") (10 8201.3574660633
305.4298642534 0.0) (11 8201.3574660633 791.8552036199 0.0))
((0 . "LINE") (100 . "AcDbEntity") (8 . "WINDOWS") (62 . 7) (370 . 13) (100 . "AcDbLine") (10 8246.6063348416
746.6063348416 0.0) (11 8495.4751131222 746.6063348416 0.0))
((0 . "LINE") (100 . "AcDbEntity") (8 . "WINDOWS") (62 . 7) (370 . 13) (100 . "AcDbLine") (10 8495.4751131222
746.6063348416 0.0) (11 8495.4751131222 361.9909502262 0.0))
((0 . "LINE") (100 . "AcDbEntity") (8 . "WINDOWS") (62 . 7) (370 . 13) (100 . "AcDbLine") (10 8495.4751131222
361.9909502262 0.0) (11 8246.6063348416 361.9909502262 0.0))
((0 . "LINE") (100 . "AcDbEntity") (8 . "WINDOWS") (62 . 7) (370 . 13) (100 . "AcDbLine") (10 8246.6063348416
361.9909502262 0.0) (11 8246.6063348416 746.6063348416 0.0))
((0 . "LINE") (100 . "AcDbEntity") (8 . "WINDOWS") (62 . 7) (370 . 13) (100 . "AcDbLine") (10 8902.7149321267
791.8552036199 0.0) (11 9242.0814479638 791.8552036199 0.0))
((0 . "LINE") (100 . "AcDbEntity") (8 . "WINDOWS") (62 . 7) (370 . 13) (100 . "AcDbLine") (10 9242.0814479638
791.8552036199 0.0) (11 9242.0814479638 305.4298642534 0.0))
((0 . "LINE") (100 . "AcDbEntity") (8 . "WINDOWS") (62 . 7) (370 . 13) (100 . "AcDbLine") (10 9242.0814479638
305.4298642534 0.0) (11 8902.7149321267 305.4298642534 0.0))
((0 . "LINE") (100 . "AcDbEntity") (8 . "WINDOWS") (62 . 7) (370 . 13) (100 . "AcDbLine") (10 8902.7149321267
305.4298642534 0.0) (11 8902.7149321267 791.8552036199 0.0))
((0 . "LINE") (100 . "AcDbEntity") (8 . "WINDOWS") (62 . 7) (370 . 13) (100 . "AcDbLine") (10 8947.963800905
746.6063348416 0.0) (11 9196.8325791855 746.6063348416 0.0))
((0 . "LINE") (100 . "AcDbEntity") (8 . "WINDOWS") (62 . 7) (370 . 13) (100 . "AcDbLine") (10 9196.8325791855
746.6063348416 0.0) (11 9196.8325791855 361.9909502262 0.0))
((0 . "LINE") (100 . "AcDbEntity") (8 . "WINDOWS") (62 . 7) (370 . 13) (100 . "AcDbLine") (10 9196.8325791855
361.9909502262 0.0) (11 8947.963800905 361.9909502262 0.0))
((0 . "LINE") (100 . "AcDbEntity") (8 . "WINDOWS") (62 . 7) (370 . 13) (100 . "AcDbLine") (10 8947.963800905
361.9909502262 0.0) (11 8947.963800905 746.6063348416 0.0))
((0 . "LINE") (100 . "AcDbEntity") (8 . "WINDOWS") (62 . 7) (370 . 13) (100 . "AcDbLine") (10 8665.1583710407
2556.5610859729 0.0) (11 8846.1538461538 2556.5610859729 0.0))
((0 . "LINE") (100 . "AcDbEntity") (8 . "WINDOWS") (62 . 7) (370 . 13) (100 . "AcDbLine") (10 8846.1538461538
2556.5610859729 0.0) (11 8817.8932139859 2396.4175036879 0.0))
((0 . "LINE") (100 . "AcDbEntity") (8 . "WINDOWS") (62 . 7) (370 . 13) (100 . "AcDbLine") (10 8817.8932139859
2396.4175036879 0.0) (11 8812.2171945701 2364.2533936652 0.0))
((0 . "LINE") (100 . "AcDbEntity") (8 . "WINDOWS") (62 . 7) (370 . 13) (100 . "AcDbLine") (10 8812.2171945701
2364.2533936652 0.0) (11 8699.0950226244 2364.2533936652 0.0))
((0 . "LINE") (100 . "AcDbEntity") (8 . "WINDOWS") (62 . 7) (370 . 13) (100 . "AcDbLine") (10 8699.0950226244
2364.2533936652 0.0) (11 8693.4190032087 2396.4175036879 0.0))
((0 . "LINE") (100 . "AcDbEntity") (8 . "WINDOWS") (62 . 7) (370 . 13) (100 . "AcDbLine") (10 8693.4190032087
2396.4175036879 0.0) (11 8665.1583710407 2556.5610859729 0.0))
((0 . "LINE") (100 . "AcDbEntity") (8 . "WINDOWS") (62 . 7) (370 . 13) (100 . "AcDbLine") (10 10712.6696832579
5113.1221719457 0.0) (11 10712.6696832579 4909.5022624434 0.0))
((0 . "LINE") (100 . "AcDbEntity") (8 . "WINDOWS") (62 . 7) (370 . 13) (100 . "AcDbLine") (10 10712.6696832579
4909.5022624434 0.0) (11 10712.6696832579 3280.5429864253 0.0))
((0 . "LINE") (100 . "AcDbEntity") (8 . "WINDOWS") (62 . 7) (370 . 13) (100 . "AcDbLine") (10 11798.6425339367
5113.1221719457 0.0) (11 11798.6425339367 4909.5022624434 0.0))
((0 . "LINE") (100 . "AcDbEntity") (8 . "WINDOWS") (62 . 7) (370 . 13) (100 . "AcDbLine") (10 11798.6425339367
4909.5022624434 0.0) (11 11798.6425339367 3280.5429864253 0.0))
((0 . "LINE") (100 . "AcDbEntity") (8 . "WINDOWS") (62 . 7) (370 . 13) (100 . "AcDbLine") (10 10712.6696832579
3280.5429864253 0.0) (11 10803.1674208145 3280.5429864253 0.0))
((0 . "LINE") (100 . "AcDbEntity") (8 . "WINDOWS") (62 . 7) (370 . 13) (100 . "AcDbLine") (10 10803.1674208145
3280.5429864253 0.0) (11 10848.4162895928 3280.5429864253 0.0))
((0 . "LINE") (100 . "AcDbEntity") (8 . "WINDOWS") (62 . 7) (370 . 13) (100 . "AcDbLine") (10 10848.4162895928
3280.5429864253 0.0) (11 11662.8959276018 3280.5429864253 0.0))
((0 . "LINE") (100 . "AcDbEntity") (8 . "WINDOWS") (62 . 7) (370 . 13) (100 . "AcDbLine") (10 11662.8959276018
3280.5429864253 0.0) (11 11708.1447963801 3280.5429864253 0.0))
((0 . "LINE") (100 . "AcDbEntity") (8 . "WINDOWS") (62 . 7) (370 . 13) (100 . "AcDbLine") (10 11708.1447963801
3280.5429864253 0.0) (11 11798.6425339367 3280.5429864253 0.0))
((0 . "LINE") (100 . "AcDbEntity") (8 . "WINDOWS") (62 . 7) (370 . 13) (100 . "AcDbLine") (10 10803.1674208145
5067.8733031674 0.0) (11 10803.1674208145 3280.5429864253 0.0))
((0 . "LINE") (100 . "AcDbEntity") (8 . "WINDOWS") (62 . 7) (370 . 13) (100 . "AcDbLine") (10 11708.1447963801
5067.8733031674 0.0) (11 11708.1447963801 3280.5429864253 0.0))
((0 . "LINE") (100 . "AcDbEntity") (8 . "WINDOWS") (62 . 7) (370 . 13) (100 . "AcDbLine") (10 10848.4162895928
5022.6244343891 0.0) (11 10848.4162895928 4389.1402714932 0.0))
((0 . "LINE") (100 . "AcDbEntity") (8 . "WINDOWS") (62 . 7) (370 . 13) (100 . "AcDbLine") (10 10848.4162895928
4389.1402714932 0.0) (11 10848.4162895928 3280.5429864253 0.0))
((0 . "LINE") (100 . "AcDbEntity") (8 . "WINDOWS") (62 . 7) (370 . 13) (100 . "AcDbLine") (10 11662.8959276018
5022.6244343891 0.0) (11 11662.8959276018 4389.1402714932 0.0))
((0 . "LINE") (100 . "AcDbEntity") (8 . "WINDOWS") (62 . 7) (370 . 13) (100 . "AcDbLine") (10 11662.8959276018
4389.1402714932 0.0) (11 11662.8959276018 3280.5429864253 0.0))
((0 . "LINE") (100 . "AcDbEntity") (8 . "WINDOWS") (62 . 7) (370 . 13) (100 . "AcDbLine") (10 11221.7194570136
5213.8390258257 0.0) (11 11221.7194570136 4389.1402714932 0.0))
((0 . "LINE") (100 . "AcDbEntity") (8 . "WINDOWS") (62 . 7) (370 . 13) (100 . "AcDbLine") (10 11289.592760181
5213.8390258257 0.0) (11 11289.592760181 4389.1402714932 0.0))
((0 . "LINE") (100 . "AcDbEntity") (8 . "WINDOWS") (62 . 7) (370 . 13) (100 . "AcDbLine") (10 10848.4162895928
4389.1402714932 0.0) (11 11221.7194570136 4389.1402714932 0.0))
((0 . "LINE") (100 . "AcDbEntity") (8 . "WINDOWS") (62 . 7) (370 . 13) (100 . "AcDbLine") (10 11221.7194570136
4389.1402714932 0.0) (11 11289.592760181 4389.1402714932 0.0))
((0 . "LINE") (100 . "AcDbEntity") (8 . "WINDOWS") (62 . 7) (370 . 13) (100 . "AcDbLine") (10 11289.592760181
4389.1402714932 0.0) (11 11662.8959276018 4389.1402714932 0.0))
((0 . "LINE") (100 . "AcDbEntity") (8 . "WINDOWS") (62 . 7) (370 . 13) (100 . "AcDbLine") (10 10904.9773755656
4276.0180995475 0.0) (11 11606.334841629 4276.0180995475 0.0))
((0 . "LINE") (100 . "AcDbEntity") (8 . "WINDOWS") (62 . 7) (370 . 13) (100 . "AcDbLine") (10 11606.334841629
4276.0180995475 0.0) (11 11606.334841629 3337.1040723982 0.0))
((0 . "LINE") (100 . "AcDbEntity") (8 . "WINDOWS") (62 . 7) (370 . 13) (100 . "AcDbLine") (10 11606.334841629
3337.1040723982 0.0) (11 10904.9773755656 3337.1040723982 0.0))
((0 . "LINE") (100 . "AcDbEntity") (8 . "WINDOWS") (62 . 7) (370 . 13) (100 . "AcDbLine") (10 10904.9773755656
3337.1040723982 0.0) (11 10904.9773755656 4276.0180995475 0.0))
((0 . "LINE") (100 . "AcDbEntity") (8 . "WINDOWS") (62 . 7) (370 . 13) (100 . "AcDbLine") (10 10871.0407239819
4321.2669683258 0.0) (11 11640.2714932127 4321.2669683258 0.0))
((0 . "LINE") (100 . "AcDbEntity") (8 . "WINDOWS") (62 . 7) (370 . 13) (100 . "AcDbLine") (10 11640.2714932127
4321.2669683258 0.0) (11 11640.2714932127 3291.8552036199 0.0))
((0 . "LINE") (100 . "AcDbEntity") (8 . "WINDOWS") (62 . 7) (370 . 13) (100 . "AcDbLine") (10 11640.2714932127
3291.8552036199 0.0) (11 10871.0407239819 3291.8552036199 0.0))
((0 . "LINE") (100 . "AcDbEntity") (8 . "WINDOWS") (62 . 7) (370 . 13) (100 . "AcDbLine") (10 10871.0407239819
3291.8552036199 0.0) (11 10871.0407239819 4321.2669683258 0.0))
((0 . "LINE") (100 . "AcDbEntity") (8 . "WINDOWS") (62 . 7) (370 . 13) (100 . "AcDbLine") (10 10463.8009049774
2058.8235294118 0.0) (11 10463.8009049774 192.3076923077 0.0))
((0 . "LINE") (100 . "AcDbEntity") (8 . "WINDOWS") (62 . 7) (370 . 13) (100 . "AcDbLine") (10 12047.5113122172
2058.8235294118 0.0) (11 12047.5113122172 192.3076923077 0.0))
((0 . "LINE") (100 . "AcDbEntity") (8 . "WINDOWS") (62 . 7) (370 . 13) (100 . "AcDbLine") (10 10463.8009049774
192.3076923077 0.0) (11 10542.9864253394 192.3076923077 0.0))
((0 . "LINE") (100 . "AcDbEntity") (8 . "WINDOWS") (62 . 7) (370 . 13) (100 . "AcDbLine") (10 10542.9864253394
192.3076923077 0.0) (11 10599.5475113122 192.3076923077 0.0))
((0 . "LINE") (100 . "AcDbEntity") (8 . "WINDOWS") (62 . 7) (370 . 13) (100 . "AcDbLine") (10 10599.5475113122
192.3076923077 0.0) (11 11210.407239819 192.3076923077 0.0))
((0 . "LINE") (100 . "AcDbEntity") (8 . "WINDOWS") (62 . 7) (370 . 13) (100 . "AcDbLine") (10 11210.407239819
192.3076923077 0.0) (11 11300.9049773756 192.3076923077 0.0))
((0 . "LINE") (100 . "AcDbEntity") (8 . "WINDOWS") (62 . 7) (370 . 13) (100 . "AcDbLine") (10 11300.9049773756
192.3076923077 0.0) (11 11911.7647058824 192.3076923077 0.0))
((0 . "LINE") (100 . "AcDbEntity") (8 . "WINDOWS") (62 . 7) (370 . 13) (100 . "AcDbLine") (10 11911.7647058824
192.3076923077 0.0) (11 11968.3257918552 192.3076923077 0.0))
((0 . "LINE") (100 . "AcDbEntity") (8 . "WINDOWS") (62 . 7) (370 . 13) (100 . "AcDbLine") (10 11968.3257918552
192.3076923077 0.0) (11 12036.1990950226 192.3076923077 0.0))
((0 . "LINE") (100 . "AcDbEntity") (8 . "WINDOWS") (62 . 7) (370 . 13) (100 . "AcDbLine") (10 12036.1990950226
192.3076923077 0.0) (11 12047.5113122172 192.3076923077 0.0))
((0 . "LINE") (100 . "AcDbEntity") (8 . "WINDOWS") (62 . 7) (370 . 13) (100 . "AcDbLine") (10 10542.9864253394
2024.8868778281 0.0) (11 10542.9864253394 192.3076923077 0.0))
((0 . "LINE") (100 . "AcDbEntity") (8 . "WINDOWS") (62 . 7) (370 . 13) (100 . "AcDbLine") (10 11968.3257918552
2024.8868778281 0.0) (11 11968.3257918552 192.3076923077 0.0))
((0 . "LINE") (100 . "AcDbEntity") (8 . "WINDOWS") (62 . 7) (370 . 13) (100 . "AcDbLine") (10 10599.5475113122
1979.6380090498 0.0) (11 10599.5475113122 984.1628959276 0.0))
((0 . "LINE") (100 . "AcDbEntity") (8 . "WINDOWS") (62 . 7) (370 . 13) (100 . "AcDbLine") (10 10599.5475113122
984.1628959276 0.0) (11 10599.5475113122 904.9773755656 0.0))
((0 . "LINE") (100 . "AcDbEntity") (8 . "WINDOWS") (62 . 7) (370 . 13) (100 . "AcDbLine") (10 10599.5475113122
904.9773755656 0.0) (11 10599.5475113122 192.3076923077 0.0))
((0 . "LINE") (100 . "AcDbEntity") (8 . "WINDOWS") (62 . 7) (370 . 13) (100 . "AcDbLine") (10 11911.7647058824
1979.6380090498 0.0) (11 11911.7647058824 984.1628959276 0.0))
((0 . "LINE") (100 . "AcDbEntity") (8 . "WINDOWS") (62 . 7) (370 . 13) (100 . "AcDbLine") (10 11911.7647058824
984.1628959276 0.0) (11 11911.7647058824 904.9773755656 0.0))
((0 . "LINE") (100 . "AcDbEntity") (8 . "WINDOWS") (62 . 7) (370 . 13) (100 . "AcDbLine") (10 11911.7647058824
904.9773755656 0.0) (11 11911.7647058824 192.3076923077 0.0))
((0 . "LINE") (100 . "AcDbEntity") (8 . "WINDOWS") (62 . 7) (370 . 13) (100 . "AcDbLine") (10 11210.407239819
2227.4714479638 0.0) (11 11210.407239819 984.1628959276 0.0))
((0 . "LINE") (100 . "AcDbEntity") (8 . "WINDOWS") (62 . 7) (370 . 13) (100 . "AcDbLine") (10 11210.407239819
984.1628959276 0.0) (11 11210.407239819 904.9773755656 0.0))
((0 . "LINE") (100 . "AcDbEntity") (8 . "WINDOWS") (62 . 7) (370 . 13) (100 . "AcDbLine") (10 11210.407239819
904.9773755656 0.0) (11 11210.407239819 192.3076923077 0.0))
((0 . "LINE") (100 . "AcDbEntity") (8 . "WINDOWS") (62 . 7) (370 . 13) (100 . "AcDbLine") (10 11300.9049773756
2227.4714479638 0.0) (11 11300.9049773756 984.1628959276 0.0))
((0 . "LINE") (100 . "AcDbEntity") (8 . "WINDOWS") (62 . 7) (370 . 13) (100 . "AcDbLine") (10 11300.9049773756
984.1628959276 0.0) (11 11300.9049773756 904.9773755656 0.0))
((0 . "LINE") (100 . "AcDbEntity") (8 . "WINDOWS") (62 . 7) (370 . 13) (100 . "AcDbLine") (10 11300.9049773756
904.9773755656 0.0) (11 11300.9049773756 192.3076923077 0.0))
((0 . "LINE") (100 . "AcDbEntity") (8 . "WINDOWS") (62 . 7) (370 . 13) (100 . "AcDbLine") (10 10599.5475113122
984.1628959276 0.0) (11 11210.407239819 984.1628959276 0.0))
((0 . "LINE") (100 . "AcDbEntity") (8 . "WINDOWS") (62 . 7) (370 . 13) (100 . "AcDbLine") (10 11210.407239819
984.1628959276 0.0) (11 11300.9049773756 984.1628959276 0.0))
((0 . "LINE") (100 . "AcDbEntity") (8 . "WINDOWS") (62 . 7) (370 . 13) (100 . "AcDbLine") (10 11300.9049773756
984.1628959276 0.0) (11 11911.7647058824 984.1628959276 0.0))
((0 . "LINE") (100 . "AcDbEntity") (8 . "WINDOWS") (62 . 7) (370 . 13) (100 . "AcDbLine") (10 10599.5475113122
904.9773755656 0.0) (11 11210.407239819 904.9773755656 0.0))
((0 . "LINE") (100 . "AcDbEntity") (8 . "WINDOWS") (62 . 7) (370 . 13) (100 . "AcDbLine") (10 11210.407239819
904.9773755656 0.0) (11 11300.9049773756 904.9773755656 0.0))
((0 . "LINE") (100 . "AcDbEntity") (8 . "WINDOWS") (62 . 7) (370 . 13) (100 . "AcDbLine") (10 11300.9049773756
904.9773755656 0.0) (11 11911.7647058824 904.9773755656 0.0))
((0 . "LINE") (100 . "AcDbEntity") (8 . "WINDOWS") (62 . 7) (370 . 13) (100 . "AcDbLine") (10 10701.3574660633
791.8552036199 0.0) (11 11040.7239819005 791.8552036199 0.0))
((0 . "LINE") (100 . "AcDbEntity") (8 . "WINDOWS") (62 . 7) (370 . 13) (100 . "AcDbLine") (10 11040.7239819005
791.8552036199 0.0) (11 11040.7239819005 305.4298642534 0.0))
((0 . "LINE") (100 . "AcDbEntity") (8 . "WINDOWS") (62 . 7) (370 . 13) (100 . "AcDbLine") (10 11040.7239819005
305.4298642534 0.0) (11 10701.3574660633 305.4298642534 0.0))
((0 . "LINE") (100 . "AcDbEntity") (8 . "WINDOWS") (62 . 7) (370 . 13) (100 . "AcDbLine") (10 10701.3574660633
305.4298642534 0.0) (11 10701.3574660633 791.8552036199 0.0))
((0 . "LINE") (100 . "AcDbEntity") (8 . "WINDOWS") (62 . 7) (370 . 13) (100 . "AcDbLine") (10 10746.6063348416
746.6063348416 0.0) (11 10995.4751131222 746.6063348416 0.0))
((0 . "LINE") (100 . "AcDbEntity") (8 . "WINDOWS") (62 . 7) (370 . 13) (100 . "AcDbLine") (10 10995.4751131222
746.6063348416 0.0) (11 10995.4751131222 361.9909502262 0.0))
((0 . "LINE") (100 . "AcDbEntity") (8 . "WINDOWS") (62 . 7) (370 . 13) (100 . "AcDbLine") (10 10995.4751131222
361.9909502262 0.0) (11 10746.6063348416 361.9909502262 0.0))
((0 . "LINE") (100 . "AcDbEntity") (8 . "WINDOWS") (62 . 7) (370 . 13) (100 . "AcDbLine") (10 10746.6063348416
361.9909502262 0.0) (11 10746.6063348416 746.6063348416 0.0))
((0 . "LINE") (100 . "AcDbEntity") (8 . "WINDOWS") (62 . 7) (370 . 13) (100 . "AcDbLine") (10 11402.7149321267
791.8552036199 0.0) (11 11742.0814479638 791.8552036199 0.0))
((0 . "LINE") (100 . "AcDbEntity") (8 . "WINDOWS") (62 . 7) (370 . 13) (100 . "AcDbLine") (10 11742.0814479638
791.8552036199 0.0) (11 11742.0814479638 305.4298642534 0.0))
((0 . "LINE") (100 . "AcDbEntity") (8 . "WINDOWS") (62 . 7) (370 . 13) (100 . "AcDbLine") (10 11742.0814479638
305.4298642534 0.0) (11 11402.7149321267 305.4298642534 0.0))
((0 . "LINE") (100 . "AcDbEntity") (8 . "WINDOWS") (62 . 7) (370 . 13) (100 . "AcDbLine") (10 11402.7149321267
305.4298642534 0.0) (11 11402.7149321267 791.8552036199 0.0))
((0 . "LINE") (100 . "AcDbEntity") (8 . "WINDOWS") (62 . 7) (370 . 13) (100 . "AcDbLine") (10 11447.963800905
746.6063348416 0.0) (11 11696.8325791855 746.6063348416 0.0))
((0 . "LINE") (100 . "AcDbEntity") (8 . "WINDOWS") (62 . 7) (370 . 13) (100 . "AcDbLine") (10 11696.8325791855
746.6063348416 0.0) (11 11696.8325791855 361.9909502262 0.0))
((0 . "LINE") (100 . "AcDbEntity") (8 . "WINDOWS") (62 . 7) (370 . 13) (100 . "AcDbLine") (10 11696.8325791855
361.9909502262 0.0) (11 11447.963800905 361.9909502262 0.0))
((0 . "LINE") (100 . "AcDbEntity") (8 . "WINDOWS") (62 . 7) (370 . 13) (100 . "AcDbLine") (10 11447.963800905
361.9909502262 0.0) (11 11447.963800905 746.6063348416 0.0))
((0 . "LINE") (100 . "AcDbEntity") (8 . "WINDOWS") (62 . 7) (370 . 13) (100 . "AcDbLine") (10 11165.1583710407
2556.5610859729 0.0) (11 11346.1538461538 2556.5610859729 0.0))
((0 . "LINE") (100 . "AcDbEntity") (8 . "WINDOWS") (62 . 7) (370 . 13) (100 . "AcDbLine") (10 11346.1538461538
2556.5610859729 0.0) (11 11317.8932139859 2396.4175036879 0.0))
((0 . "LINE") (100 . "AcDbEntity") (8 . "WINDOWS") (62 . 7) (370 . 13) (100 . "AcDbLine") (10 11317.8932139859
2396.4175036879 0.0) (11 11312.2171945701 2364.2533936652 0.0))
((0 . "LINE") (100 . "AcDbEntity") (8 . "WINDOWS") (62 . 7) (370 . 13) (100 . "AcDbLine") (10 11312.2171945701
2364.2533936652 0.0) (11 11199.0950226244 2364.2533936652 0.0))
((0 . "LINE") (100 . "AcDbEntity") (8 . "WINDOWS") (62 . 7) (370 . 13) (100 . "AcDbLine") (10 11199.0950226244
2364.2533936652 0.0) (11 11193.4190032087 2396.4175036879 0.0))
((0 . "LINE") (100 . "AcDbEntity") (8 . "WINDOWS") (62 . 7) (370 . 13) (100 . "AcDbLine") (10 11193.4190032087
2396.4175036879 0.0) (11 11165.1583710407 2556.5610859729 0.0))
((0 . "LINE") (100 . "AcDbEntity") (8 . "SOLAR") (62 . 7) (370 . 13) (100 . "AcDbLine") (10 4162.8959276018
8212.6696832579 0.0) (11 4966.0633484163 8212.6696832579 0.0))
((0 . "LINE") (100 . "AcDbEntity") (8 . "SOLAR") (62 . 7) (370 . 13) (100 . "AcDbLine") (10 4966.0633484163
8212.6696832579 0.0) (11 5214.9321266968 7873.3031674208 0.0))
((0 . "LINE") (100 . "AcDbEntity") (8 . "SOLAR") (62 . 7) (370 . 13) (100 . "AcDbLine") (10 5214.9321266968
7873.3031674208 0.0) (11 4366.5158371041 7873.3031674208 0.0))
((0 . "LINE") (100 . "AcDbEntity") (8 . "SOLAR") (62 . 7) (370 . 13) (100 . "AcDbLine") (10 4366.5158371041
7873.3031674208 0.0) (11 4162.8959276018 8212.6696832579 0.0))
((0 . "LINE") (100 . "AcDbEntity") (8 . "SOLAR") (62 . 7) (370 . 13) (100 . "AcDbLine") (10 4203.4502262443
8178.7330316742 0.0) (11 4452.4886877828 8178.7330316742 0.0))
((0 . "LINE") (100 . "AcDbEntity") (8 . "SOLAR") (62 . 7) (370 . 13) (100 . "AcDbLine") (10 4452.4886877828
8178.7330316742 0.0) (11 4721.7194570136 8178.7330316742 0.0))
((0 . "LINE") (100 . "AcDbEntity") (8 . "SOLAR") (62 . 7) (370 . 13) (100 . "AcDbLine") (10 4721.7194570136
8178.7330316742 0.0) (11 4970.757918552 8178.7330316742 0.0))
((0 . "LINE") (100 . "AcDbEntity") (8 . "SOLAR") (62 . 7) (370 . 13) (100 . "AcDbLine") (10 4970.757918552
8178.7330316742 0.0) (11 4980.4196832579 8165.4977375566 0.0))
((0 . "LINE") (100 . "AcDbEntity") (8 . "SOLAR") (62 . 7) (370 . 13) (100 . "AcDbLine") (10 4980.4196832579
8165.4977375566 0.0) (11 5021.6060520362 8109.0780542986 0.0))
((0 . "LINE") (100 . "AcDbEntity") (8 . "SOLAR") (62 . 7) (370 . 13) (100 . "AcDbLine") (10 5021.6060520362
8109.0780542986 0.0) (11 5054.5551470588 8063.9423076923 0.0))
((0 . "LINE") (100 . "AcDbEntity") (8 . "SOLAR") (62 . 7) (370 . 13) (100 . "AcDbLine") (10 5054.5551470588
8063.9423076923 0.0) (11 5094.5647624434 8009.1346153846 0.0))
((0 . "LINE") (100 . "AcDbEntity") (8 . "SOLAR") (62 . 7) (370 . 13) (100 . "AcDbLine") (10 5094.5647624434
8009.1346153846 0.0) (11 5120.4533371041 7973.6708144796 0.0))
((0 . "LINE") (100 . "AcDbEntity") (8 . "SOLAR") (62 . 7) (370 . 13) (100 . "AcDbLine") (10 5120.4533371041
7973.6708144796 0.0) (11 5143.9884049774 7941.4309954751 0.0))
((0 . "LINE") (100 . "AcDbEntity") (8 . "SOLAR") (62 . 7) (370 . 13) (100 . "AcDbLine") (10 5143.9884049774
7941.4309954751 0.0) (11 5168.9479638009 7907.2398190045 0.0))
((0 . "LINE") (100 . "AcDbEntity") (8 . "SOLAR") (62 . 7) (370 . 13) (100 . "AcDbLine") (10 5168.9479638009
7907.2398190045 0.0) (11 4908.7481108597 7907.2398190045 0.0))
((0 . "LINE") (100 . "AcDbEntity") (8 . "SOLAR") (62 . 7) (370 . 13) (100 . "AcDbLine") (10 4908.7481108597
7907.2398190045 0.0) (11 4627.4509841629 7907.2398190045 0.0))
((0 . "LINE") (100 . "AcDbEntity") (8 . "SOLAR") (62 . 7) (370 . 13) (100 . "AcDbLine") (10 4627.4509841629
7907.2398190045 0.0) (11 4367.2511312217 7907.2398190045 0.0))
((0 . "LINE") (100 . "AcDbEntity") (8 . "SOLAR") (62 . 7) (370 . 13) (100 . "AcDbLine") (10 4367.2511312217
7907.2398190045 0.0) (11 4346.6224547511 7941.4309954751 0.0))
((0 . "LINE") (100 . "AcDbEntity") (8 . "SOLAR") (62 . 7) (370 . 13) (100 . "AcDbLine") (10 4346.6224547511
7941.4309954751 0.0) (11 4327.1710972851 7973.6708144796 0.0))
((0 . "LINE") (100 . "AcDbEntity") (8 . "SOLAR") (62 . 7) (370 . 13) (100 . "AcDbLine") (10 4327.1710972851
7973.6708144796 0.0) (11 4305.7746040724 8009.1346153846 0.0))
((0 . "LINE") (100 . "AcDbEntity") (8 . "SOLAR") (62 . 7) (370 . 13) (100 . "AcDbLine") (10 4305.7746040724
8009.1346153846 0.0) (11 4272.7072963801 8063.9423076923 0.0))
((0 . "LINE") (100 . "AcDbEntity") (8 . "SOLAR") (62 . 7) (370 . 13) (100 . "AcDbLine") (10 4272.7072963801
8063.9423076923 0.0) (11 4245.4753959276 8109.0780542986 0.0))
((0 . "LINE") (100 . "AcDbEntity") (8 . "SOLAR") (62 . 7) (370 . 13) (100 . "AcDbLine") (10 4245.4753959276
8109.0780542986 0.0) (11 4211.435520362 8165.4977375566 0.0))
((0 . "LINE") (100 . "AcDbEntity") (8 . "SOLAR") (62 . 7) (370 . 13) (100 . "AcDbLine") (10 4211.435520362
8165.4977375566 0.0) (11 4203.4502262443 8178.7330316742 0.0))
((0 . "LINE") (100 . "AcDbEntity") (8 . "SOLAR") (62 . 7) (370 . 13) (100 . "AcDbLine") (10 4452.4886877828
8178.7330316742 0.0) (11 4461.0180995475 8165.4977375566 0.0))
((0 . "LINE") (100 . "AcDbEntity") (8 . "SOLAR") (62 . 7) (370 . 13) (100 . "AcDbLine") (10 4461.0180995475
8165.4977375566 0.0) (11 4497.3774547511 8109.0780542986 0.0))
((0 . "LINE") (100 . "AcDbEntity") (8 . "SOLAR") (62 . 7) (370 . 13) (100 . "AcDbLine") (10 4497.3774547511
8109.0780542986 0.0) (11 4526.4649321267 8063.9423076923 0.0))
((0 . "LINE") (100 . "AcDbEntity") (8 . "SOLAR") (62 . 7) (370 . 13) (100 . "AcDbLine") (10 4526.4649321267
8063.9423076923 0.0) (11 4561.7854411765 8009.1346153846 0.0))
((0 . "LINE") (100 . "AcDbEntity") (8 . "SOLAR") (62 . 7) (370 . 13) (100 . "AcDbLine") (10 4561.7854411765
8009.1346153846 0.0) (11 4584.63989819 7973.6708144796 0.0))
((0 . "LINE") (100 . "AcDbEntity") (8 . "SOLAR") (62 . 7) (370 . 13) (100 . "AcDbLine") (10 4584.63989819
7973.6708144796 0.0) (11 4605.4166628959 7941.4309954751 0.0))
((0 . "LINE") (100 . "AcDbEntity") (8 . "SOLAR") (62 . 7) (370 . 13) (100 . "AcDbLine") (10 4605.4166628959
7941.4309954751 0.0) (11 4627.4509841629 7907.2398190045 0.0))
((0 . "LINE") (100 . "AcDbEntity") (8 . "SOLAR") (62 . 7) (370 . 13) (100 . "AcDbLine") (10 4721.7194570136
8178.7330316742 0.0) (11 4730.8371040724 8165.4977375566 0.0))
((0 . "LINE") (100 . "AcDbEntity") (8 . "SOLAR") (62 . 7) (370 . 13) (100 . "AcDbLine") (10 4730.8371040724
8165.4977375566 0.0) (11 4769.7039932127 8109.0780542986 0.0))
((0 . "LINE") (100 . "AcDbEntity") (8 . "SOLAR") (62 . 7) (370 . 13) (100 . "AcDbLine") (10 4769.7039932127
8109.0780542986 0.0) (11 4800.7975113122 8063.9423076923 0.0))
((0 . "LINE") (100 . "AcDbEntity") (8 . "SOLAR") (62 . 7) (370 . 13) (100 . "AcDbLine") (10 4800.7975113122
8063.9423076923 0.0) (11 4838.5539253394 8009.1346153846 0.0))
((0 . "LINE") (100 . "AcDbEntity") (8 . "SOLAR") (62 . 7) (370 . 13) (100 . "AcDbLine") (10 4838.5539253394
8009.1346153846 0.0) (11 4862.9845361991 7973.6708144796 0.0))
((0 . "LINE") (100 . "AcDbEntity") (8 . "SOLAR") (62 . 7) (370 . 13) (100 . "AcDbLine") (10 4862.9845361991
7973.6708144796 0.0) (11 4885.1941968326 7941.4309954751 0.0))
((0 . "LINE") (100 . "AcDbEntity") (8 . "SOLAR") (62 . 7) (370 . 13) (100 . "AcDbLine") (10 4885.1941968326
7941.4309954751 0.0) (11 4908.7481108597 7907.2398190045 0.0))
((0 . "LINE") (100 . "AcDbEntity") (8 . "SOLAR") (62 . 7) (370 . 13) (100 . "AcDbLine") (10 4211.435520362
8165.4977375566 0.0) (11 4461.0180995475 8165.4977375566 0.0))
((0 . "LINE") (100 . "AcDbEntity") (8 . "SOLAR") (62 . 7) (370 . 13) (100 . "AcDbLine") (10 4461.0180995475
8165.4977375566 0.0) (11 4730.8371040724 8165.4977375566 0.0))
((0 . "LINE") (100 . "AcDbEntity") (8 . "SOLAR") (62 . 7) (370 . 13) (100 . "AcDbLine") (10 4730.8371040724
8165.4977375566 0.0) (11 4980.4196832579 8165.4977375566 0.0))
((0 . "LINE") (100 . "AcDbEntity") (8 . "SOLAR") (62 . 7) (370 . 13) (100 . "AcDbLine") (10 4245.4753959276
8109.0780542986 0.0) (11 4497.3774547511 8109.0780542986 0.0))
((0 . "LINE") (100 . "AcDbEntity") (8 . "SOLAR") (62 . 7) (370 . 13) (100 . "AcDbLine") (10 4497.3774547511
8109.0780542986 0.0) (11 4769.7039932127 8109.0780542986 0.0))
((0 . "LINE") (100 . "AcDbEntity") (8 . "SOLAR") (62 . 7) (370 . 13) (100 . "AcDbLine") (10 4769.7039932127
8109.0780542986 0.0) (11 5021.6060520362 8109.0780542986 0.0))
((0 . "LINE") (100 . "AcDbEntity") (8 . "SOLAR") (62 . 7) (370 . 13) (100 . "AcDbLine") (10 4272.7072963801
8063.9423076923 0.0) (11 4526.4649321267 8063.9423076923 0.0))
((0 . "LINE") (100 . "AcDbEntity") (8 . "SOLAR") (62 . 7) (370 . 13) (100 . "AcDbLine") (10 4526.4649321267
8063.9423076923 0.0) (11 4800.7975113122 8063.9423076923 0.0))
((0 . "LINE") (100 . "AcDbEntity") (8 . "SOLAR") (62 . 7) (370 . 13) (100 . "AcDbLine") (10 4800.7975113122
8063.9423076923 0.0) (11 5054.5551470588 8063.9423076923 0.0))
((0 . "LINE") (100 . "AcDbEntity") (8 . "SOLAR") (62 . 7) (370 . 13) (100 . "AcDbLine") (10 4305.7746040724
8009.1346153846 0.0) (11 4561.7854411765 8009.1346153846 0.0))
((0 . "LINE") (100 . "AcDbEntity") (8 . "SOLAR") (62 . 7) (370 . 13) (100 . "AcDbLine") (10 4561.7854411765
8009.1346153846 0.0) (11 4838.5539253394 8009.1346153846 0.0))
((0 . "LINE") (100 . "AcDbEntity") (8 . "SOLAR") (62 . 7) (370 . 13) (100 . "AcDbLine") (10 4838.5539253394
8009.1346153846 0.0) (11 5094.5647624434 8009.1346153846 0.0))
((0 . "LINE") (100 . "AcDbEntity") (8 . "SOLAR") (62 . 7) (370 . 13) (100 . "AcDbLine") (10 4327.1710972851
7973.6708144796 0.0) (11 4584.63989819 7973.6708144796 0.0))
((0 . "LINE") (100 . "AcDbEntity") (8 . "SOLAR") (62 . 7) (370 . 13) (100 . "AcDbLine") (10 4584.63989819
7973.6708144796 0.0) (11 4862.9845361991 7973.6708144796 0.0))
((0 . "LINE") (100 . "AcDbEntity") (8 . "SOLAR") (62 . 7) (370 . 13) (100 . "AcDbLine") (10 4862.9845361991
7973.6708144796 0.0) (11 5120.4533371041 7973.6708144796 0.0))
((0 . "LINE") (100 . "AcDbEntity") (8 . "SOLAR") (62 . 7) (370 . 13) (100 . "AcDbLine") (10 4346.6224547511
7941.4309954751 0.0) (11 4605.4166628959 7941.4309954751 0.0))
((0 . "LINE") (100 . "AcDbEntity") (8 . "SOLAR") (62 . 7) (370 . 13) (100 . "AcDbLine") (10 4605.4166628959
7941.4309954751 0.0) (11 4885.1941968326 7941.4309954751 0.0))
((0 . "LINE") (100 . "AcDbEntity") (8 . "SOLAR") (62 . 7) (370 . 13) (100 . "AcDbLine") (10 4885.1941968326
7941.4309954751 0.0) (11 5143.9884049774 7941.4309954751 0.0))
((0 . "LINE") (100 . "AcDbEntity") (8 . "SOLAR") (62 . 7) (370 . 13) (100 . "AcDbLine") (10 5000 8212.6696832579 0.0)
(11 5780.5429864253 8212.6696832579 0.0))
((0 . "LINE") (100 . "AcDbEntity") (8 . "SOLAR") (62 . 7) (370 . 13) (100 . "AcDbLine") (10 5780.5429864253
8212.6696832579 0.0) (11 6029.4117647059 7873.3031674208 0.0))
((0 . "LINE") (100 . "AcDbEntity") (8 . "SOLAR") (62 . 7) (370 . 13) (100 . "AcDbLine") (10 6029.4117647059
7873.3031674208 0.0) (11 5248.8687782805 7873.3031674208 0.0))
((0 . "LINE") (100 . "AcDbEntity") (8 . "SOLAR") (62 . 7) (370 . 13) (100 . "AcDbLine") (10 5248.8687782805
7873.3031674208 0.0) (11 5000 8212.6696832579 0.0))
((0 . "LINE") (100 . "AcDbEntity") (8 . "SOLAR") (62 . 7) (370 . 13) (100 . "AcDbLine") (10 5044.4004524887
8178.7330316742 0.0) (11 5285.0678733032 8178.7330316742 0.0))
((0 . "LINE") (100 . "AcDbEntity") (8 . "SOLAR") (62 . 7) (370 . 13) (100 . "AcDbLine") (10 5285.0678733032
8178.7330316742 0.0) (11 5545.2488687783 8178.7330316742 0.0))
((0 . "LINE") (100 . "AcDbEntity") (8 . "SOLAR") (62 . 7) (370 . 13) (100 . "AcDbLine") (10 5545.2488687783
8178.7330316742 0.0) (11 5785.9162895928 8178.7330316742 0.0))
((0 . "LINE") (100 . "AcDbEntity") (8 . "SOLAR") (62 . 7) (370 . 13) (100 . "AcDbLine") (10 5785.9162895928
8178.7330316742 0.0) (11 5795.6221719457 8165.4977375566 0.0))
((0 . "LINE") (100 . "AcDbEntity") (8 . "SOLAR") (62 . 7) (370 . 13) (100 . "AcDbLine") (10 5795.6221719457
8165.4977375566 0.0) (11 5836.9966063348 8109.0780542986 0.0))
((0 . "LINE") (100 . "AcDbEntity") (8 . "SOLAR") (62 . 7) (370 . 13) (100 . "AcDbLine") (10 5836.9966063348
8109.0780542986 0.0) (11 5871.278280543 8062.3303167421 0.0))
((0 . "LINE") (100 . "AcDbEntity") (8 . "SOLAR") (62 . 7) (370 . 13) (100 . "AcDbLine") (10 5871.278280543
8062.3303167421 0.0) (11 5910.2884615385 8009.1346153846 0.0))
((0 . "LINE") (100 . "AcDbEntity") (8 . "SOLAR") (62 . 7) (370 . 13) (100 . "AcDbLine") (10 5910.2884615385
8009.1346153846 0.0) (11 5935.1131221719 7975.2828054299 0.0))
((0 . "LINE") (100 . "AcDbEntity") (8 . "SOLAR") (62 . 7) (370 . 13) (100 . "AcDbLine") (10 5935.1131221719
7975.2828054299 0.0) (11 5959.9377828054 7941.4309954751 0.0))
((0 . "LINE") (100 . "AcDbEntity") (8 . "SOLAR") (62 . 7) (370 . 13) (100 . "AcDbLine") (10 5959.9377828054
7941.4309954751 0.0) (11 5985.0113122172 7907.2398190045 0.0))
((0 . "LINE") (100 . "AcDbEntity") (8 . "SOLAR") (62 . 7) (370 . 13) (100 . "AcDbLine") (10 5985.0113122172
7907.2398190045 0.0) (11 5744.3438914027 7907.2398190045 0.0))
((0 . "LINE") (100 . "AcDbEntity") (8 . "SOLAR") (62 . 7) (370 . 13) (100 . "AcDbLine") (10 5744.3438914027
7907.2398190045 0.0) (11 5484.1628959276 7907.2398190045 0.0))
((0 . "LINE") (100 . "AcDbEntity") (8 . "SOLAR") (62 . 7) (370 . 13) (100 . "AcDbLine") (10 5484.1628959276
7907.2398190045 0.0) (11 5243.4954751131 7907.2398190045 0.0))
((0 . "LINE") (100 . "AcDbEntity") (8 . "SOLAR") (62 . 7) (370 . 13) (100 . "AcDbLine") (10 5243.4954751131
7907.2398190045 0.0) (11 5218.4219457014 7941.4309954751 0.0))
((0 . "LINE") (100 . "AcDbEntity") (8 . "SOLAR") (62 . 7) (370 . 13) (100 . "AcDbLine") (10 5218.4219457014
7941.4309954751 0.0) (11 5193.5972850679 7975.2828054299 0.0))
((0 . "LINE") (100 . "AcDbEntity") (8 . "SOLAR") (62 . 7) (370 . 13) (100 . "AcDbLine") (10 5193.5972850679
7975.2828054299 0.0) (11 5168.7726244344 8009.1346153846 0.0))
((0 . "LINE") (100 . "AcDbEntity") (8 . "SOLAR") (62 . 7) (370 . 13) (100 . "AcDbLine") (10 5168.7726244344
8009.1346153846 0.0) (11 5129.7624434389 8062.3303167421 0.0))
((0 . "LINE") (100 . "AcDbEntity") (8 . "SOLAR") (62 . 7) (370 . 13) (100 . "AcDbLine") (10 5129.7624434389
8062.3303167421 0.0) (11 5095.4807692308 8109.0780542986 0.0))
((0 . "LINE") (100 . "AcDbEntity") (8 . "SOLAR") (62 . 7) (370 . 13) (100 . "AcDbLine") (10 5095.4807692308
8109.0780542986 0.0) (11 5054.1063348416 8165.4977375566 0.0))
((0 . "LINE") (100 . "AcDbEntity") (8 . "SOLAR") (62 . 7) (370 . 13) (100 . "AcDbLine") (10 5054.1063348416
8165.4977375566 0.0) (11 5044.4004524887 8178.7330316742 0.0))
((0 . "LINE") (100 . "AcDbEntity") (8 . "SOLAR") (62 . 7) (370 . 13) (100 . "AcDbLine") (10 5285.0678733032
8178.7330316742 0.0) (11 5294.7737556561 8165.4977375566 0.0))
((0 . "LINE") (100 . "AcDbEntity") (8 . "SOLAR") (62 . 7) (370 . 13) (100 . "AcDbLine") (10 5294.7737556561
8165.4977375566 0.0) (11 5336.1481900452 8109.0780542986 0.0))
((0 . "LINE") (100 . "AcDbEntity") (8 . "SOLAR") (62 . 7) (370 . 13) (100 . "AcDbLine") (10 5336.1481900452
8109.0780542986 0.0) (11 5370.4298642534 8062.3303167421 0.0))
((0 . "LINE") (100 . "AcDbEntity") (8 . "SOLAR") (62 . 7) (370 . 13) (100 . "AcDbLine") (10 5370.4298642534
8062.3303167421 0.0) (11 5409.4400452489 8009.1346153846 0.0))
((0 . "LINE") (100 . "AcDbEntity") (8 . "SOLAR") (62 . 7) (370 . 13) (100 . "AcDbLine") (10 5409.4400452489
8009.1346153846 0.0) (11 5434.2647058824 7975.2828054299 0.0))
((0 . "LINE") (100 . "AcDbEntity") (8 . "SOLAR") (62 . 7) (370 . 13) (100 . "AcDbLine") (10 5434.2647058824
7975.2828054299 0.0) (11 5459.0893665158 7941.4309954751 0.0))
((0 . "LINE") (100 . "AcDbEntity") (8 . "SOLAR") (62 . 7) (370 . 13) (100 . "AcDbLine") (10 5459.0893665158
7941.4309954751 0.0) (11 5484.1628959276 7907.2398190045 0.0))
((0 . "LINE") (100 . "AcDbEntity") (8 . "SOLAR") (62 . 7) (370 . 13) (100 . "AcDbLine") (10 5545.2488687783
8178.7330316742 0.0) (11 5554.9547511312 8165.4977375566 0.0))
((0 . "LINE") (100 . "AcDbEntity") (8 . "SOLAR") (62 . 7) (370 . 13) (100 . "AcDbLine") (10 5554.9547511312
8165.4977375566 0.0) (11 5596.3291855204 8109.0780542986 0.0))
((0 . "LINE") (100 . "AcDbEntity") (8 . "SOLAR") (62 . 7) (370 . 13) (100 . "AcDbLine") (10 5596.3291855204
8109.0780542986 0.0) (11 5630.6108597285 8062.3303167421 0.0))
((0 . "LINE") (100 . "AcDbEntity") (8 . "SOLAR") (62 . 7) (370 . 13) (100 . "AcDbLine") (10 5630.6108597285
8062.3303167421 0.0) (11 5669.621040724 8009.1346153846 0.0))
((0 . "LINE") (100 . "AcDbEntity") (8 . "SOLAR") (62 . 7) (370 . 13) (100 . "AcDbLine") (10 5669.621040724
8009.1346153846 0.0) (11 5694.4457013575 7975.2828054299 0.0))
((0 . "LINE") (100 . "AcDbEntity") (8 . "SOLAR") (62 . 7) (370 . 13) (100 . "AcDbLine") (10 5694.4457013575
7975.2828054299 0.0) (11 5719.270361991 7941.4309954751 0.0))
((0 . "LINE") (100 . "AcDbEntity") (8 . "SOLAR") (62 . 7) (370 . 13) (100 . "AcDbLine") (10 5719.270361991
7941.4309954751 0.0) (11 5744.3438914027 7907.2398190045 0.0))
((0 . "LINE") (100 . "AcDbEntity") (8 . "SOLAR") (62 . 7) (370 . 13) (100 . "AcDbLine") (10 5054.1063348416
8165.4977375566 0.0) (11 5294.7737556561 8165.4977375566 0.0))
((0 . "LINE") (100 . "AcDbEntity") (8 . "SOLAR") (62 . 7) (370 . 13) (100 . "AcDbLine") (10 5294.7737556561
8165.4977375566 0.0) (11 5554.9547511312 8165.4977375566 0.0))
((0 . "LINE") (100 . "AcDbEntity") (8 . "SOLAR") (62 . 7) (370 . 13) (100 . "AcDbLine") (10 5554.9547511312
8165.4977375566 0.0) (11 5795.6221719457 8165.4977375566 0.0))
((0 . "LINE") (100 . "AcDbEntity") (8 . "SOLAR") (62 . 7) (370 . 13) (100 . "AcDbLine") (10 5095.4807692308
8109.0780542986 0.0) (11 5336.1481900452 8109.0780542986 0.0))
((0 . "LINE") (100 . "AcDbEntity") (8 . "SOLAR") (62 . 7) (370 . 13) (100 . "AcDbLine") (10 5336.1481900452
8109.0780542986 0.0) (11 5596.3291855204 8109.0780542986 0.0))
((0 . "LINE") (100 . "AcDbEntity") (8 . "SOLAR") (62 . 7) (370 . 13) (100 . "AcDbLine") (10 5596.3291855204
8109.0780542986 0.0) (11 5836.9966063348 8109.0780542986 0.0))
((0 . "LINE") (100 . "AcDbEntity") (8 . "SOLAR") (62 . 7) (370 . 13) (100 . "AcDbLine") (10 5129.7624434389
8062.3303167421 0.0) (11 5370.4298642534 8062.3303167421 0.0))
((0 . "LINE") (100 . "AcDbEntity") (8 . "SOLAR") (62 . 7) (370 . 13) (100 . "AcDbLine") (10 5370.4298642534
8062.3303167421 0.0) (11 5630.6108597285 8062.3303167421 0.0))
((0 . "LINE") (100 . "AcDbEntity") (8 . "SOLAR") (62 . 7) (370 . 13) (100 . "AcDbLine") (10 5630.6108597285
8062.3303167421 0.0) (11 5871.278280543 8062.3303167421 0.0))
((0 . "LINE") (100 . "AcDbEntity") (8 . "SOLAR") (62 . 7) (370 . 13) (100 . "AcDbLine") (10 5168.7726244344
8009.1346153846 0.0) (11 5409.4400452489 8009.1346153846 0.0))
((0 . "LINE") (100 . "AcDbEntity") (8 . "SOLAR") (62 . 7) (370 . 13) (100 . "AcDbLine") (10 5409.4400452489
8009.1346153846 0.0) (11 5669.621040724 8009.1346153846 0.0))
((0 . "LINE") (100 . "AcDbEntity") (8 . "SOLAR") (62 . 7) (370 . 13) (100 . "AcDbLine") (10 5669.621040724
8009.1346153846 0.0) (11 5910.2884615385 8009.1346153846 0.0))
((0 . "LINE") (100 . "AcDbEntity") (8 . "SOLAR") (62 . 7) (370 . 13) (100 . "AcDbLine") (10 5193.5972850679
7975.2828054299 0.0) (11 5434.2647058824 7975.2828054299 0.0))
((0 . "LINE") (100 . "AcDbEntity") (8 . "SOLAR") (62 . 7) (370 . 13) (100 . "AcDbLine") (10 5434.2647058824
7975.2828054299 0.0) (11 5694.4457013575 7975.2828054299 0.0))
((0 . "LINE") (100 . "AcDbEntity") (8 . "SOLAR") (62 . 7) (370 . 13) (100 . "AcDbLine") (10 5694.4457013575
7975.2828054299 0.0) (11 5935.1131221719 7975.2828054299 0.0))
((0 . "LINE") (100 . "AcDbEntity") (8 . "SOLAR") (62 . 7) (370 . 13) (100 . "AcDbLine") (10 5218.4219457014
7941.4309954751 0.0) (11 5459.0893665158 7941.4309954751 0.0))
((0 . "LINE") (100 . "AcDbEntity") (8 . "SOLAR") (62 . 7) (370 . 13) (100 . "AcDbLine") (10 5459.0893665158
7941.4309954751 0.0) (11 5719.270361991 7941.4309954751 0.0))
((0 . "LINE") (100 . "AcDbEntity") (8 . "SOLAR") (62 . 7) (370 . 13) (100 . "AcDbLine") (10 5719.270361991
7941.4309954751 0.0) (11 5959.9377828054 7941.4309954751 0.0))
((0 . "LINE") (100 . "AcDbEntity") (8 . "SOLAR") (62 . 7) (370 . 13) (100 . "AcDbLine") (10 5814.4796380091
8212.6696832579 0.0) (11 6606.334841629 8212.6696832579 0.0))
((0 . "LINE") (100 . "AcDbEntity") (8 . "SOLAR") (62 . 7) (370 . 13) (100 . "AcDbLine") (10 6606.334841629
8212.6696832579 0.0) (11 6843.8914027149 7873.3031674208 0.0))
((0 . "LINE") (100 . "AcDbEntity") (8 . "SOLAR") (62 . 7) (370 . 13) (100 . "AcDbLine") (10 6843.8914027149
7873.3031674208 0.0) (11 6063.3484162896 7873.3031674208 0.0))
((0 . "LINE") (100 . "AcDbEntity") (8 . "SOLAR") (62 . 7) (370 . 13) (100 . "AcDbLine") (10 6063.3484162896
7873.3031674208 0.0) (11 5814.4796380091 8212.6696832579 0.0))
((0 . "LINE") (100 . "AcDbEntity") (8 . "SOLAR") (62 . 7) (370 . 13) (100 . "AcDbLine") (10 5859.1346153846
8178.7330316742 0.0) (11 6102.9411764706 8178.7330316742 0.0))
((0 . "LINE") (100 . "AcDbEntity") (8 . "SOLAR") (62 . 7) (370 . 13) (100 . "AcDbLine") (10 6102.9411764706
8178.7330316742 0.0) (11 6366.5158371041 8178.7330316742 0.0))
((0 . "LINE") (100 . "AcDbEntity") (8 . "SOLAR") (62 . 7) (370 . 13) (100 . "AcDbLine") (10 6366.5158371041
8178.7330316742 0.0) (11 6610.32239819 8178.7330316742 0.0))
((0 . "LINE") (100 . "AcDbEntity") (8 . "SOLAR") (62 . 7) (370 . 13) (100 . "AcDbLine") (10 6610.32239819
8178.7330316742 0.0) (11 6619.5981334842 8165.4977375566 0.0))
((0 . "LINE") (100 . "AcDbEntity") (8 . "SOLAR") (62 . 7) (370 . 13) (100 . "AcDbLine") (10 6619.5981334842
8165.4977375566 0.0) (11 6659.1389253394 8109.0780542986 0.0))
((0 . "LINE") (100 . "AcDbEntity") (8 . "SOLAR") (62 . 7) (370 . 13) (100 . "AcDbLine") (10 6659.1389253394
8109.0780542986 0.0) (11 6690.771561086 8063.9423076923 0.0))
((0 . "LINE") (100 . "AcDbEntity") (8 . "SOLAR") (62 . 7) (370 . 13) (100 . "AcDbLine") (10 6690.771561086
8063.9423076923 0.0) (11 6729.1826244344 8009.1346153846 0.0))
((0 . "LINE") (100 . "AcDbEntity") (8 . "SOLAR") (62 . 7) (370 . 13) (100 . "AcDbLine") (10 6729.1826244344
8009.1346153846 0.0) (11 6752.9071040724 7975.2828054299 0.0))
((0 . "LINE") (100 . "AcDbEntity") (8 . "SOLAR") (62 . 7) (370 . 13) (100 . "AcDbLine") (10 6752.9071040724
7975.2828054299 0.0) (11 6776.6315723982 7941.4309954751 0.0))
((0 . "LINE") (100 . "AcDbEntity") (8 . "SOLAR") (62 . 7) (370 . 13) (100 . "AcDbLine") (10 6776.6315723982
7941.4309954751 0.0) (11 6800.5938914027 7907.2398190045 0.0))
((0 . "LINE") (100 . "AcDbEntity") (8 . "SOLAR") (62 . 7) (370 . 13) (100 . "AcDbLine") (10 6800.5938914027
7907.2398190045 0.0) (11 6559.5776809955 7907.2398190045 0.0))
((0 . "LINE") (100 . "AcDbEntity") (8 . "SOLAR") (62 . 7) (370 . 13) (100 . "AcDbLine") (10 6559.5776809955
7907.2398190045 0.0) (11 6299.0196040724 7907.2398190045 0.0))
((0 . "LINE") (100 . "AcDbEntity") (8 . "SOLAR") (62 . 7) (370 . 13) (100 . "AcDbLine") (10 6299.0196040724
7907.2398190045 0.0) (11 6058.0033936652 7907.2398190045 0.0))
((0 . "LINE") (100 . "AcDbEntity") (8 . "SOLAR") (62 . 7) (370 . 13) (100 . "AcDbLine") (10 6058.0033936652
7907.2398190045 0.0) (11 6032.9583597285 7941.4309954751 0.0))
((0 . "LINE") (100 . "AcDbEntity") (8 . "SOLAR") (62 . 7) (370 . 13) (100 . "AcDbLine") (10 6032.9583597285
7941.4309954751 0.0) (11 6008.1619117647 7975.2828054299 0.0))
((0 . "LINE") (100 . "AcDbEntity") (8 . "SOLAR") (62 . 7) (370 . 13) (100 . "AcDbLine") (10 6008.1619117647
7975.2828054299 0.0) (11 5983.3654524887 8009.1346153846 0.0))
((0 . "LINE") (100 . "AcDbEntity") (8 . "SOLAR") (62 . 7) (370 . 13) (100 . "AcDbLine") (10 5983.3654524887
8009.1346153846 0.0) (11 5943.2188235294 8063.9423076923 0.0))
((0 . "LINE") (100 . "AcDbEntity") (8 . "SOLAR") (62 . 7) (370 . 13) (100 . "AcDbLine") (10 5943.2188235294
8063.9423076923 0.0) (11 5910.1568891403 8109.0780542986 0.0))
((0 . "LINE") (100 . "AcDbEntity") (8 . "SOLAR") (62 . 7) (370 . 13) (100 . "AcDbLine") (10 5910.1568891403
8109.0780542986 0.0) (11 5868.8294683258 8165.4977375566 0.0))
((0 . "LINE") (100 . "AcDbEntity") (8 . "SOLAR") (62 . 7) (370 . 13) (100 . "AcDbLine") (10 5868.8294683258
8165.4977375566 0.0) (11 5859.1346153846 8178.7330316742 0.0))
((0 . "LINE") (100 . "AcDbEntity") (8 . "SOLAR") (62 . 7) (370 . 13) (100 . "AcDbLine") (10 6102.9411764706
8178.7330316742 0.0) (11 6112.5 8165.4977375566 0.0))
((0 . "LINE") (100 . "AcDbEntity") (8 . "SOLAR") (62 . 7) (370 . 13) (100 . "AcDbLine") (10 6112.5 8165.4977375566 0.0)
(11 6153.2475452489 8109.0780542986 0.0))
((0 . "LINE") (100 . "AcDbEntity") (8 . "SOLAR") (62 . 7) (370 . 13) (100 . "AcDbLine") (10 6153.2475452489
8109.0780542986 0.0) (11 6185.8455882353 8063.9423076923 0.0))
((0 . "LINE") (100 . "AcDbEntity") (8 . "SOLAR") (62 . 7) (370 . 13) (100 . "AcDbLine") (10 6185.8455882353
8063.9423076923 0.0) (11 6225.4289253394 8009.1346153846 0.0))
((0 . "LINE") (100 . "AcDbEntity") (8 . "SOLAR") (62 . 7) (370 . 13) (100 . "AcDbLine") (10 6225.4289253394
8009.1346153846 0.0) (11 6249.8774547511 7975.2828054299 0.0))
((0 . "LINE") (100 . "AcDbEntity") (8 . "SOLAR") (62 . 7) (370 . 13) (100 . "AcDbLine") (10 6249.8774547511
7975.2828054299 0.0) (11 6274.3259841629 7941.4309954751 0.0))
((0 . "LINE") (100 . "AcDbEntity") (8 . "SOLAR") (62 . 7) (370 . 13) (100 . "AcDbLine") (10 6274.3259841629
7941.4309954751 0.0) (11 6299.0196040724 7907.2398190045 0.0))
((0 . "LINE") (100 . "AcDbEntity") (8 . "SOLAR") (62 . 7) (370 . 13) (100 . "AcDbLine") (10 6366.5158371041
8178.7330316742 0.0) (11 6375.92760181 8165.4977375566 0.0))
((0 . "LINE") (100 . "AcDbEntity") (8 . "SOLAR") (62 . 7) (370 . 13) (100 . "AcDbLine") (10 6375.92760181
8165.4977375566 0.0) (11 6416.0482692308 8109.0780542986 0.0))
((0 . "LINE") (100 . "AcDbEntity") (8 . "SOLAR") (62 . 7) (370 . 13) (100 . "AcDbLine") (10 6416.0482692308
8109.0780542986 0.0) (11 6448.1447963801 8063.9423076923 0.0))
((0 . "LINE") (100 . "AcDbEntity") (8 . "SOLAR") (62 . 7) (370 . 13) (100 . "AcDbLine") (10 6448.1447963801
8063.9423076923 0.0) (11 6487.1191515837 8009.1346153846 0.0))
((0 . "LINE") (100 . "AcDbEntity") (8 . "SOLAR") (62 . 7) (370 . 13) (100 . "AcDbLine") (10 6487.1191515837
8009.1346153846 0.0) (11 6511.1915497738 7975.2828054299 0.0))
((0 . "LINE") (100 . "AcDbEntity") (8 . "SOLAR") (62 . 7) (370 . 13) (100 . "AcDbLine") (10 6511.1915497738
7975.2828054299 0.0) (11 6535.2639479638 7941.4309954751 0.0))
((0 . "LINE") (100 . "AcDbEntity") (8 . "SOLAR") (62 . 7) (370 . 13) (100 . "AcDbLine") (10 6535.2639479638
7941.4309954751 0.0) (11 6559.5776809955 7907.2398190045 0.0))
((0 . "LINE") (100 . "AcDbEntity") (8 . "SOLAR") (62 . 7) (370 . 13) (100 . "AcDbLine") (10 5868.8294683258
8165.4977375566 0.0) (11 6112.5 8165.4977375566 0.0))
((0 . "LINE") (100 . "AcDbEntity") (8 . "SOLAR") (62 . 7) (370 . 13) (100 . "AcDbLine") (10 6112.5 8165.4977375566 0.0)
(11 6375.92760181 8165.4977375566 0.0))
((0 . "LINE") (100 . "AcDbEntity") (8 . "SOLAR") (62 . 7) (370 . 13) (100 . "AcDbLine") (10 6375.92760181
8165.4977375566 0.0) (11 6619.5981334842 8165.4977375566 0.0))
((0 . "LINE") (100 . "AcDbEntity") (8 . "SOLAR") (62 . 7) (370 . 13) (100 . "AcDbLine") (10 5910.1568891403
8109.0780542986 0.0) (11 6153.2475452489 8109.0780542986 0.0))
((0 . "LINE") (100 . "AcDbEntity") (8 . "SOLAR") (62 . 7) (370 . 13) (100 . "AcDbLine") (10 6153.2475452489
8109.0780542986 0.0) (11 6416.0482692308 8109.0780542986 0.0))
((0 . "LINE") (100 . "AcDbEntity") (8 . "SOLAR") (62 . 7) (370 . 13) (100 . "AcDbLine") (10 6416.0482692308
8109.0780542986 0.0) (11 6659.1389253394 8109.0780542986 0.0))
((0 . "LINE") (100 . "AcDbEntity") (8 . "SOLAR") (62 . 7) (370 . 13) (100 . "AcDbLine") (10 5943.2188235294
8063.9423076923 0.0) (11 6185.8455882353 8063.9423076923 0.0))
((0 . "LINE") (100 . "AcDbEntity") (8 . "SOLAR") (62 . 7) (370 . 13) (100 . "AcDbLine") (10 6185.8455882353
8063.9423076923 0.0) (11 6448.1447963801 8063.9423076923 0.0))
((0 . "LINE") (100 . "AcDbEntity") (8 . "SOLAR") (62 . 7) (370 . 13) (100 . "AcDbLine") (10 6448.1447963801
8063.9423076923 0.0) (11 6690.771561086 8063.9423076923 0.0))
((0 . "LINE") (100 . "AcDbEntity") (8 . "SOLAR") (62 . 7) (370 . 13) (100 . "AcDbLine") (10 5983.3654524887
8009.1346153846 0.0) (11 6225.4289253394 8009.1346153846 0.0))
((0 . "LINE") (100 . "AcDbEntity") (8 . "SOLAR") (62 . 7) (370 . 13) (100 . "AcDbLine") (10 6225.4289253394
8009.1346153846 0.0) (11 6487.1191515837 8009.1346153846 0.0))
((0 . "LINE") (100 . "AcDbEntity") (8 . "SOLAR") (62 . 7) (370 . 13) (100 . "AcDbLine") (10 6487.1191515837
8009.1346153846 0.0) (11 6729.1826244344 8009.1346153846 0.0))
((0 . "LINE") (100 . "AcDbEntity") (8 . "SOLAR") (62 . 7) (370 . 13) (100 . "AcDbLine") (10 6008.1619117647
7975.2828054299 0.0) (11 6249.8774547511 7975.2828054299 0.0))
((0 . "LINE") (100 . "AcDbEntity") (8 . "SOLAR") (62 . 7) (370 . 13) (100 . "AcDbLine") (10 6249.8774547511
7975.2828054299 0.0) (11 6511.1915497738 7975.2828054299 0.0))
((0 . "LINE") (100 . "AcDbEntity") (8 . "SOLAR") (62 . 7) (370 . 13) (100 . "AcDbLine") (10 6511.1915497738
7975.2828054299 0.0) (11 6752.9071040724 7975.2828054299 0.0))
((0 . "LINE") (100 . "AcDbEntity") (8 . "SOLAR") (62 . 7) (370 . 13) (100 . "AcDbLine") (10 6032.9583597285
7941.4309954751 0.0) (11 6274.3259841629 7941.4309954751 0.0))
((0 . "LINE") (100 . "AcDbEntity") (8 . "SOLAR") (62 . 7) (370 . 13) (100 . "AcDbLine") (10 6274.3259841629
7941.4309954751 0.0) (11 6535.2639479638 7941.4309954751 0.0))
((0 . "LINE") (100 . "AcDbEntity") (8 . "SOLAR") (62 . 7) (370 . 13) (100 . "AcDbLine") (10 6535.2639479638
7941.4309954751 0.0) (11 6776.6315723982 7941.4309954751 0.0))
((0 . "LINE") (100 . "AcDbEntity") (8 . "SOLAR") (62 . 7) (370 . 13) (100 . "AcDbLine") (10 6640.2714932127
8212.6696832579 0.0) (11 7330.3167420814 8212.6696832579 0.0))
((0 . "LINE") (100 . "AcDbEntity") (8 . "SOLAR") (62 . 7) (370 . 13) (100 . "AcDbLine") (10 7330.3167420814
8212.6696832579 0.0) (11 7545.2488687783 7873.3031674208 0.0))
((0 . "LINE") (100 . "AcDbEntity") (8 . "SOLAR") (62 . 7) (370 . 13) (100 . "AcDbLine") (10 7545.2488687783
7873.3031674208 0.0) (11 6889.1402714932 7873.3031674208 0.0))
((0 . "LINE") (100 . "AcDbEntity") (8 . "SOLAR") (62 . 7) (370 . 13) (100 . "AcDbLine") (10 6889.1402714932
7873.3031674208 0.0) (11 6640.2714932127 8212.6696832579 0.0))
((0 . "LINE") (100 . "AcDbEntity") (8 . "SOLAR") (62 . 7) (370 . 13) (100 . "AcDbLine") (10 6682.3246606335
8178.7330316742 0.0) (11 6894.0422285068 8178.7330316742 0.0))
((0 . "LINE") (100 . "AcDbEntity") (8 . "SOLAR") (62 . 7) (370 . 13) (100 . "AcDbLine") (10 6894.0422285068
8178.7330316742 0.0) (11 7122.9260972851 8178.7330316742 0.0))
((0 . "LINE") (100 . "AcDbEntity") (8 . "SOLAR") (62 . 7) (370 . 13) (100 . "AcDbLine") (10 7122.9260972851
8178.7330316742 0.0) (11 7334.6436651584 8178.7330316742 0.0))
((0 . "LINE") (100 . "AcDbEntity") (8 . "SOLAR") (62 . 7) (370 . 13) (100 . "AcDbLine") (10 7334.6436651584
8178.7330316742 0.0) (11 7343.0591063348 8165.4977375566 0.0))
((0 . "LINE") (100 . "AcDbEntity") (8 . "SOLAR") (62 . 7) (370 . 13) (100 . "AcDbLine") (10 7343.0591063348
8165.4977375566 0.0) (11 7382.0075 8104.242081448 0.0))
((0 . "LINE") (100 . "AcDbEntity") (8 . "SOLAR") (62 . 7) (370 . 13) (100 . "AcDbLine") (10 7382.0075 8104.242081448
0.0) (11 7407.6314366516 8063.9423076923 0.0))
((0 . "LINE") (100 . "AcDbEntity") (8 . "SOLAR") (62 . 7) (370 . 13) (100 . "AcDbLine") (10 7407.6314366516
8063.9423076923 0.0) (11 7442.4799886878 8009.1346153846 0.0))
((0 . "LINE") (100 . "AcDbEntity") (8 . "SOLAR") (62 . 7) (370 . 13) (100 . "AcDbLine") (10 7442.4799886878
8009.1346153846 0.0) (11 7464.0040950226 7975.2828054299 0.0))
((0 . "LINE") (100 . "AcDbEntity") (8 . "SOLAR") (62 . 7) (370 . 13) (100 . "AcDbLine") (10 7464.0041063348
7975.2828054299 0.0) (11 7485.5282126697 7941.4309954751 0.0))
((0 . "LINE") (100 . "AcDbEntity") (8 . "SOLAR") (62 . 7) (370 . 13) (100 . "AcDbLine") (10 7485.5282126697
7941.4309954751 0.0) (11 7507.2680995475 7907.2398190045 0.0))
((0 . "LINE") (100 . "AcDbEntity") (8 . "SOLAR") (62 . 7) (370 . 13) (100 . "AcDbLine") (10 7507.2680995475
7907.2398190045 0.0) (11 7303.9215723982 7907.2398190045 0.0))
((0 . "LINE") (100 . "AcDbEntity") (8 . "SOLAR") (62 . 7) (370 . 13) (100 . "AcDbLine") (10 7303.9215723982
7907.2398190045 0.0) (11 7084.0874773756 7907.2398190045 0.0))
((0 . "LINE") (100 . "AcDbEntity") (8 . "SOLAR") (62 . 7) (370 . 13) (100 . "AcDbLine") (10 7084.0874773756
7907.2398190045 0.0) (11 6880.7409502262 7907.2398190045 0.0))
((0 . "LINE") (100 . "AcDbEntity") (8 . "SOLAR") (62 . 7) (370 . 13) (100 . "AcDbLine") (10 6880.7409502262
7907.2398190045 0.0) (11 6855.7528959276 7941.4309954751 0.0))
((0 . "LINE") (100 . "AcDbEntity") (8 . "SOLAR") (62 . 7) (370 . 13) (100 . "AcDbLine") (10 6855.7528959276
7941.4309954751 0.0) (11 6831.0128733032 7975.2828054299 0.0))
((0 . "LINE") (100 . "AcDbEntity") (8 . "SOLAR") (62 . 7) (370 . 13) (100 . "AcDbLine") (10 6831.0128733032
7975.2828054299 0.0) (11 6806.2728393665 8009.1346153846 0.0))
((0 . "LINE") (100 . "AcDbEntity") (8 . "SOLAR") (62 . 7) (370 . 13) (100 . "AcDbLine") (10 6806.2728393665
8009.1346153846 0.0) (11 6766.2175452489 8063.9423076923 0.0))
((0 . "LINE") (100 . "AcDbEntity") (8 . "SOLAR") (62 . 7) (370 . 13) (100 . "AcDbLine") (10 6766.2175452489
8063.9423076923 0.0) (11 6736.7651357466 8104.242081448 0.0))
((0 . "LINE") (100 . "AcDbEntity") (8 . "SOLAR") (62 . 7) (370 . 13) (100 . "AcDbLine") (10 6736.7651357466
8104.242081448 0.0) (11 6691.9974547511 8165.4977375566 0.0))
((0 . "LINE") (100 . "AcDbEntity") (8 . "SOLAR") (62 . 7) (370 . 13) (100 . "AcDbLine") (10 6691.9974547511
8165.4977375566 0.0) (11 6682.3246606335 8178.7330316742 0.0))
((0 . "LINE") (100 . "AcDbEntity") (8 . "SOLAR") (62 . 7) (370 . 13) (100 . "AcDbLine") (10 6894.0422285068
8178.7330316742 0.0) (11 6903.3069343891 8165.4977375566 0.0))
((0 . "LINE") (100 . "AcDbEntity") (8 . "SOLAR") (62 . 7) (370 . 13) (100 . "AcDbLine") (10 6903.3069343891
8165.4977375566 0.0) (11 6946.1858936652 8104.242081448 0.0))
((0 . "LINE") (100 . "AcDbEntity") (8 . "SOLAR") (62 . 7) (370 . 13) (100 . "AcDbLine") (10 6946.1858936652
8104.242081448 0.0) (11 6974.3957352941 8063.9423076923 0.0))
((0 . "LINE") (100 . "AcDbEntity") (8 . "SOLAR") (62 . 7) (370 . 13) (100 . "AcDbLine") (10 6974.3957352941
8063.9423076923 0.0) (11 7012.7611199095 8009.1346153846 0.0))
((0 . "LINE") (100 . "AcDbEntity") (8 . "SOLAR") (62 . 7) (370 . 13) (100 . "AcDbLine") (10 7012.7611199095
8009.1346153846 0.0) (11 7036.4573868778 7975.2828054299 0.0))
((0 . "LINE") (100 . "AcDbEntity") (8 . "SOLAR") (62 . 7) (370 . 13) (100 . "AcDbLine") (10 7036.4573868778
7975.2828054299 0.0) (11 7060.1536538462 7941.4309954751 0.0))
((0 . "LINE") (100 . "AcDbEntity") (8 . "SOLAR") (62 . 7) (370 . 13) (100 . "AcDbLine") (10 7060.1536538462
7941.4309954751 0.0) (11 7084.0874773756 7907.2398190045 0.0))
((0 . "LINE") (100 . "AcDbEntity") (8 . "SOLAR") (62 . 7) (370 . 13) (100 . "AcDbLine") (10 7122.9260972851
8178.7330316742 0.0) (11 7131.7496266968 8165.4977375566 0.0))
((0 . "LINE") (100 . "AcDbEntity") (8 . "SOLAR") (62 . 7) (370 . 13) (100 . "AcDbLine") (10 7131.7496266968
8165.4977375566 0.0) (11 7172.5867307692 8104.242081448 0.0))
((0 . "LINE") (100 . "AcDbEntity") (8 . "SOLAR") (62 . 7) (370 . 13) (100 . "AcDbLine") (10 7172.5867307692
8104.242081448 0.0) (11 7199.4532466063 8063.9423076923 0.0))
((0 . "LINE") (100 . "AcDbEntity") (8 . "SOLAR") (62 . 7) (370 . 13) (100 . "AcDbLine") (10 7199.4532466063
8063.9423076923 0.0) (11 7235.9917081448 8009.1346153846 0.0))
((0 . "LINE") (100 . "AcDbEntity") (8 . "SOLAR") (62 . 7) (370 . 13) (100 . "AcDbLine") (10 7235.9917081448
8009.1346153846 0.0) (11 7258.559581448 7975.2828054299 0.0))
((0 . "LINE") (100 . "AcDbEntity") (8 . "SOLAR") (62 . 7) (370 . 13) (100 . "AcDbLine") (10 7258.559581448
7975.2828054299 0.0) (11 7281.1274547511 7941.4309954751 0.0))
((0 . "LINE") (100 . "AcDbEntity") (8 . "SOLAR") (62 . 7) (370 . 13) (100 . "AcDbLine") (10 7281.1274547511
7941.4309954751 0.0) (11 7303.9215723982 7907.2398190045 0.0))
((0 . "LINE") (100 . "AcDbEntity") (8 . "SOLAR") (62 . 7) (370 . 13) (100 . "AcDbLine") (10 6691.9974547511
8165.4977375566 0.0) (11 6903.3069343891 8165.4977375566 0.0))
((0 . "LINE") (100 . "AcDbEntity") (8 . "SOLAR") (62 . 7) (370 . 13) (100 . "AcDbLine") (10 6903.3069343891
8165.4977375566 0.0) (11 7131.7496266968 8165.4977375566 0.0))
((0 . "LINE") (100 . "AcDbEntity") (8 . "SOLAR") (62 . 7) (370 . 13) (100 . "AcDbLine") (10 7131.7496266968
8165.4977375566 0.0) (11 7343.0591063348 8165.4977375566 0.0))
((0 . "LINE") (100 . "AcDbEntity") (8 . "SOLAR") (62 . 7) (370 . 13) (100 . "AcDbLine") (10 6736.7651357466
8104.242081448 0.0) (11 6946.1858936652 8104.242081448 0.0))
((0 . "LINE") (100 . "AcDbEntity") (8 . "SOLAR") (62 . 7) (370 . 13) (100 . "AcDbLine") (10 6946.1858936652
8104.242081448 0.0) (11 7172.5867307692 8104.242081448 0.0))
((0 . "LINE") (100 . "AcDbEntity") (8 . "SOLAR") (62 . 7) (370 . 13) (100 . "AcDbLine") (10 7172.5867307692
8104.242081448 0.0) (11 7382.0075 8104.242081448 0.0))
((0 . "LINE") (100 . "AcDbEntity") (8 . "SOLAR") (62 . 7) (370 . 13) (100 . "AcDbLine") (10 6766.2175452489
8063.9423076923 0.0) (11 6974.3957352941 8063.9423076923 0.0))
((0 . "LINE") (100 . "AcDbEntity") (8 . "SOLAR") (62 . 7) (370 . 13) (100 . "AcDbLine") (10 6974.3957352941
8063.9423076923 0.0) (11 7199.4532466063 8063.9423076923 0.0))
((0 . "LINE") (100 . "AcDbEntity") (8 . "SOLAR") (62 . 7) (370 . 13) (100 . "AcDbLine") (10 7199.4532466063
8063.9423076923 0.0) (11 7407.6314366516 8063.9423076923 0.0))
((0 . "LINE") (100 . "AcDbEntity") (8 . "SOLAR") (62 . 7) (370 . 13) (100 . "AcDbLine") (10 6806.2728393665
8009.1346153846 0.0) (11 7012.7611199095 8009.1346153846 0.0))
((0 . "LINE") (100 . "AcDbEntity") (8 . "SOLAR") (62 . 7) (370 . 13) (100 . "AcDbLine") (10 7012.7611199095
8009.1346153846 0.0) (11 7235.9917081448 8009.1346153846 0.0))
((0 . "LINE") (100 . "AcDbEntity") (8 . "SOLAR") (62 . 7) (370 . 13) (100 . "AcDbLine") (10 7235.9917081448
8009.1346153846 0.0) (11 7442.4799886878 8009.1346153846 0.0))
((0 . "LINE") (100 . "AcDbEntity") (8 . "SOLAR") (62 . 7) (370 . 13) (100 . "AcDbLine") (10 6831.0128733032
7975.2828054299 0.0) (11 7036.4573868778 7975.2828054299 0.0))
((0 . "LINE") (100 . "AcDbEntity") (8 . "SOLAR") (62 . 7) (370 . 13) (100 . "AcDbLine") (10 7036.4573868778
7975.2828054299 0.0) (11 7258.559581448 7975.2828054299 0.0))
((0 . "LINE") (100 . "AcDbEntity") (8 . "SOLAR") (62 . 7) (370 . 13) (100 . "AcDbLine") (10 7258.559581448
7975.2828054299 0.0) (11 7464.0040950226 7975.2828054299 0.0))
((0 . "LINE") (100 . "AcDbEntity") (8 . "SOLAR") (62 . 7) (370 . 13) (100 . "AcDbLine") (10 6855.7528959276
7941.4309954751 0.0) (11 7060.1536538462 7941.4309954751 0.0))
((0 . "LINE") (100 . "AcDbEntity") (8 . "SOLAR") (62 . 7) (370 . 13) (100 . "AcDbLine") (10 7060.1536538462
7941.4309954751 0.0) (11 7281.1274547511 7941.4309954751 0.0))
((0 . "LINE") (100 . "AcDbEntity") (8 . "SOLAR") (62 . 7) (370 . 13) (100 . "AcDbLine") (10 7281.1274547511
7941.4309954751 0.0) (11 7485.5282126697 7941.4309954751 0.0))
((0 . "LINE") (100 . "AcDbEntity") (8 . "SOLAR") (62 . 7) (370 . 13) (100 . "AcDbLine") (10 7692.3076923077
8212.6696832579 0.0) (11 8518.0995475113 8212.6696832579 0.0))
((0 . "LINE") (100 . "AcDbEntity") (8 . "SOLAR") (62 . 7) (370 . 13) (100 . "AcDbLine") (10 8518.0995475113
8212.6696832579 0.0) (11 8733.0316742081 7873.3031674208 0.0))
((0 . "LINE") (100 . "AcDbEntity") (8 . "SOLAR") (62 . 7) (370 . 13) (100 . "AcDbLine") (10 8733.0316742081
7873.3031674208 0.0) (11 7895.92760181 7873.3031674208 0.0))
((0 . "LINE") (100 . "AcDbEntity") (8 . "SOLAR") (62 . 7) (370 . 13) (100 . "AcDbLine") (10 7895.92760181
7873.3031674208 0.0) (11 7692.3076923077 8212.6696832579 0.0))
((0 . "LINE") (100 . "AcDbEntity") (8 . "SOLAR") (62 . 7) (370 . 13) (100 . "AcDbLine") (10 7733.342760181
8178.7330316742 0.0) (11 7988.3107126697 8178.7330316742 0.0))
((0 . "LINE") (100 . "AcDbEntity") (8 . "SOLAR") (62 . 7) (370 . 13) (100 . "AcDbLine") (10 7988.3107126697
8178.7330316742 0.0) (11 8263.9517307692 8178.7330316742 0.0))
((0 . "LINE") (100 . "AcDbEntity") (8 . "SOLAR") (62 . 7) (370 . 13) (100 . "AcDbLine") (10 8263.9517307692
8178.7330316742 0.0) (11 8518.9196832579 8178.7330316742 0.0))
((0 . "LINE") (100 . "AcDbEntity") (8 . "SOLAR") (62 . 7) (370 . 13) (100 . "AcDbLine") (10 8518.9196832579
8178.7330316742 0.0) (11 8527.2910067873 8165.4977375566 0.0))
((0 . "LINE") (100 . "AcDbEntity") (8 . "SOLAR") (62 . 7) (370 . 13) (100 . "AcDbLine") (10 8527.2910067873
8165.4977375566 0.0) (11 8567.0547963801 8102.6300904977 0.0))
((0 . "LINE") (100 . "AcDbEntity") (8 . "SOLAR") (62 . 7) (370 . 13) (100 . "AcDbLine") (10 8567.0547963801
8102.6300904977 0.0) (11 8591.5248190045 8063.9423076923 0.0))
((0 . "LINE") (100 . "AcDbEntity") (8 . "SOLAR") (62 . 7) (370 . 13) (100 . "AcDbLine") (10 8591.5248190045
8063.9423076923 0.0) (11 8611.9165045249 8031.7024886878 0.0))
((0 . "LINE") (100 . "AcDbEntity") (8 . "SOLAR") (62 . 7) (370 . 13) (100 . "AcDbLine") (10 8611.9165045249
8031.7024886878 0.0) (11 8633.3277714932 7997.850678733 0.0))
((0 . "LINE") (100 . "AcDbEntity") (8 . "SOLAR") (62 . 7) (370 . 13) (100 . "AcDbLine") (10 8633.3277714932
7997.850678733 0.0) (11 8660.8565497738 7954.3269230769 0.0))
((0 . "LINE") (100 . "AcDbEntity") (8 . "SOLAR") (62 . 7) (370 . 13) (100 . "AcDbLine") (10 8660.8565497738
7954.3269230769 0.0) (11 8690.6391402715 7907.2398190045 0.0))
((0 . "LINE") (100 . "AcDbEntity") (8 . "SOLAR") (62 . 7) (370 . 13) (100 . "AcDbLine") (10 8690.6391402715
7907.2398190045 0.0) (11 8432.8808484163 7907.2398190045 0.0))
((0 . "LINE") (100 . "AcDbEntity") (8 . "SOLAR") (62 . 7) (370 . 13) (100 . "AcDbLine") (10 8432.8808484163
7907.2398190045 0.0) (11 8154.2232239819 7907.2398190045 0.0))
((0 . "LINE") (100 . "AcDbEntity") (8 . "SOLAR") (62 . 7) (370 . 13) (100 . "AcDbLine") (10 8154.2232239819
7907.2398190045 0.0) (11 7896.4649321267 7907.2398190045 0.0))
((0 . "LINE") (100 . "AcDbEntity") (8 . "SOLAR") (62 . 7) (370 . 13) (100 . "AcDbLine") (10 7896.4649321267
7907.2398190045 0.0) (11 7868.1734276018 7954.3269230769 0.0))
((0 . "LINE") (100 . "AcDbEntity") (8 . "SOLAR") (62 . 7) (370 . 13) (100 . "AcDbLine") (10 7868.1734276018
7954.3269230769 0.0) (11 7842.0229072398 7997.850678733 0.0))
((0 . "LINE") (100 . "AcDbEntity") (8 . "SOLAR") (62 . 7) (370 . 13) (100 . "AcDbLine") (10 7842.0229072398
7997.850678733 0.0) (11 7821.6836085973 8031.7024886878 0.0))
((0 . "LINE") (100 . "AcDbEntity") (8 . "SOLAR") (62 . 7) (370 . 13) (100 . "AcDbLine") (10 7821.6836085973
8031.7024886878 0.0) (11 7802.3128506787 8063.9423076923 0.0))
((0 . "LINE") (100 . "AcDbEntity") (8 . "SOLAR") (62 . 7) (370 . 13) (100 . "AcDbLine") (10 7802.3128506787
8063.9423076923 0.0) (11 7779.0679411765 8102.6300904977 0.0))
((0 . "LINE") (100 . "AcDbEntity") (8 . "SOLAR") (62 . 7) (370 . 13) (100 . "AcDbLine") (10 7779.0679411765
8102.6300904977 0.0) (11 7741.2949660633 8165.4977375566 0.0))
((0 . "LINE") (100 . "AcDbEntity") (8 . "SOLAR") (62 . 7) (370 . 13) (100 . "AcDbLine") (10 7741.2949660633
8165.4977375566 0.0) (11 7733.342760181 8178.7330316742 0.0))
((0 . "LINE") (100 . "AcDbEntity") (8 . "SOLAR") (62 . 7) (370 . 13) (100 . "AcDbLine") (10 7988.3107126697
8178.7330316742 0.0) (11 7996.3989479638 8165.4977375566 0.0))
((0 . "LINE") (100 . "AcDbEntity") (8 . "SOLAR") (62 . 7) (370 . 13) (100 . "AcDbLine") (10 7996.3989479638
8165.4977375566 0.0) (11 8034.8180656109 8102.6300904977 0.0))
((0 . "LINE") (100 . "AcDbEntity") (8 . "SOLAR") (62 . 7) (370 . 13) (100 . "AcDbLine") (10 8034.8180656109
8102.6300904977 0.0) (11 8058.4605995475 8063.9423076923 0.0))
((0 . "LINE") (100 . "AcDbEntity") (8 . "SOLAR") (62 . 7) (370 . 13) (100 . "AcDbLine") (10 8058.4605995475
8063.9423076923 0.0) (11 8078.1627036199 8031.7024886878 0.0))
((0 . "LINE") (100 . "AcDbEntity") (8 . "SOLAR") (62 . 7) (370 . 13) (100 . "AcDbLine") (10 8078.1627036199
8031.7024886878 0.0) (11 8098.8499208145 7997.850678733 0.0))
((0 . "LINE") (100 . "AcDbEntity") (8 . "SOLAR") (62 . 7) (370 . 13) (100 . "AcDbLine") (10 8098.8499208145
7997.850678733 0.0) (11 8125.4477714932 7954.3269230769 0.0))
((0 . "LINE") (100 . "AcDbEntity") (8 . "SOLAR") (62 . 7) (370 . 13) (100 . "AcDbLine") (10 8125.4477714932
7954.3269230769 0.0) (11 8154.2232239819 7907.2398190045 0.0))
((0 . "LINE") (100 . "AcDbEntity") (8 . "SOLAR") (62 . 7) (370 . 13) (100 . "AcDbLine") (10 8263.9517307692
8178.7330316742 0.0) (11 8272.1870248869 8165.4977375566 0.0))
((0 . "LINE") (100 . "AcDbEntity") (8 . "SOLAR") (62 . 7) (370 . 13) (100 . "AcDbLine") (10 8272.1870248869
8165.4977375566 0.0) (11 8311.3046719457 8102.6300904977 0.0))
((0 . "LINE") (100 . "AcDbEntity") (8 . "SOLAR") (62 . 7) (370 . 13) (100 . "AcDbLine") (10 8311.3046719457
8102.6300904977 0.0) (11 8335.3770701357 8063.9423076923 0.0))
((0 . "LINE") (100 . "AcDbEntity") (8 . "SOLAR") (62 . 7) (370 . 13) (100 . "AcDbLine") (10 8335.3770701357
8063.9423076923 0.0) (11 8355.4374095023 8031.7024886878 0.0))
((0 . "LINE") (100 . "AcDbEntity") (8 . "SOLAR") (62 . 7) (370 . 13) (100 . "AcDbLine") (10 8355.4374095023
8031.7024886878 0.0) (11 8376.5007579186 7997.850678733 0.0))
((0 . "LINE") (100 . "AcDbEntity") (8 . "SOLAR") (62 . 7) (370 . 13) (100 . "AcDbLine") (10 8376.5007579186
7997.850678733 0.0) (11 8403.5822058824 7954.3269230769 0.0))
((0 . "LINE") (100 . "AcDbEntity") (8 . "SOLAR") (62 . 7) (370 . 13) (100 . "AcDbLine") (10 8403.5822058824
7954.3269230769 0.0) (11 8432.8808484163 7907.2398190045 0.0))
((0 . "LINE") (100 . "AcDbEntity") (8 . "SOLAR") (62 . 7) (370 . 13) (100 . "AcDbLine") (10 7741.2949660633
8165.4977375566 0.0) (11 7996.3989479638 8165.4977375566 0.0))
((0 . "LINE") (100 . "AcDbEntity") (8 . "SOLAR") (62 . 7) (370 . 13) (100 . "AcDbLine") (10 7996.3989479638
8165.4977375566 0.0) (11 8272.1870248869 8165.4977375566 0.0))
((0 . "LINE") (100 . "AcDbEntity") (8 . "SOLAR") (62 . 7) (370 . 13) (100 . "AcDbLine") (10 8272.1870248869
8165.4977375566 0.0) (11 8527.2910067873 8165.4977375566 0.0))
((0 . "LINE") (100 . "AcDbEntity") (8 . "SOLAR") (62 . 7) (370 . 13) (100 . "AcDbLine") (10 7779.0679411765
8102.6300904977 0.0) (11 8034.8180656109 8102.6300904977 0.0))
((0 . "LINE") (100 . "AcDbEntity") (8 . "SOLAR") (62 . 7) (370 . 13) (100 . "AcDbLine") (10 8034.8180656109
8102.6300904977 0.0) (11 8311.3046719457 8102.6300904977 0.0))
((0 . "LINE") (100 . "AcDbEntity") (8 . "SOLAR") (62 . 7) (370 . 13) (100 . "AcDbLine") (10 8311.3046719457
8102.6300904977 0.0) (11 8567.0547963801 8102.6300904977 0.0))
((0 . "LINE") (100 . "AcDbEntity") (8 . "SOLAR") (62 . 7) (370 . 13) (100 . "AcDbLine") (10 7802.3128506787
8063.9423076923 0.0) (11 8058.4605995475 8063.9423076923 0.0))
((0 . "LINE") (100 . "AcDbEntity") (8 . "SOLAR") (62 . 7) (370 . 13) (100 . "AcDbLine") (10 8058.4605995475
8063.9423076923 0.0) (11 8335.3770701357 8063.9423076923 0.0))
((0 . "LINE") (100 . "AcDbEntity") (8 . "SOLAR") (62 . 7) (370 . 13) (100 . "AcDbLine") (10 8335.3770701357
8063.9423076923 0.0) (11 8591.5248190045 8063.9423076923 0.0))
((0 . "LINE") (100 . "AcDbEntity") (8 . "SOLAR") (62 . 7) (370 . 13) (100 . "AcDbLine") (10 7821.6836085973
8031.7024886878 0.0) (11 8078.1627036199 8031.7024886878 0.0))
((0 . "LINE") (100 . "AcDbEntity") (8 . "SOLAR") (62 . 7) (370 . 13) (100 . "AcDbLine") (10 8078.1627036199
8031.7024886878 0.0) (11 8355.4374095023 8031.7024886878 0.0))
((0 . "LINE") (100 . "AcDbEntity") (8 . "SOLAR") (62 . 7) (370 . 13) (100 . "AcDbLine") (10 8355.4374095023
8031.7024886878 0.0) (11 8611.9165045249 8031.7024886878 0.0))
((0 . "LINE") (100 . "AcDbEntity") (8 . "SOLAR") (62 . 7) (370 . 13) (100 . "AcDbLine") (10 7842.0229072398
7997.850678733 0.0) (11 8098.8499208145 7997.850678733 0.0))
((0 . "LINE") (100 . "AcDbEntity") (8 . "SOLAR") (62 . 7) (370 . 13) (100 . "AcDbLine") (10 8098.8499208145
7997.850678733 0.0) (11 8376.5007579186 7997.850678733 0.0))
((0 . "LINE") (100 . "AcDbEntity") (8 . "SOLAR") (62 . 7) (370 . 13) (100 . "AcDbLine") (10 8376.5007579186
7997.850678733 0.0) (11 8633.3277714932 7997.850678733 0.0))
((0 . "LINE") (100 . "AcDbEntity") (8 . "SOLAR") (62 . 7) (370 . 13) (100 . "AcDbLine") (10 7868.1734276018
7954.3269230769 0.0) (11 8125.4477714932 7954.3269230769 0.0))
((0 . "LINE") (100 . "AcDbEntity") (8 . "SOLAR") (62 . 7) (370 . 13) (100 . "AcDbLine") (10 8125.4477714932
7954.3269230769 0.0) (11 8403.5822058824 7954.3269230769 0.0))
((0 . "LINE") (100 . "AcDbEntity") (8 . "SOLAR") (62 . 7) (370 . 13) (100 . "AcDbLine") (10 8403.5822058824
7954.3269230769 0.0) (11 8660.8565497738 7954.3269230769 0.0))
((0 . "LINE") (100 . "AcDbEntity") (8 . "SOLAR") (62 . 7) (370 . 13) (100 . "AcDbLine") (10 8563.3484162896
8212.6696832579 0.0) (11 9287.3303167421 8212.6696832579 0.0))
((0 . "LINE") (100 . "AcDbEntity") (8 . "SOLAR") (62 . 7) (370 . 13) (100 . "AcDbLine") (10 9287.3303167421
8212.6696832579 0.0) (11 9389.1402714932 7873.3031674208 0.0))
((0 . "LINE") (100 . "AcDbEntity") (8 . "SOLAR") (62 . 7) (370 . 13) (100 . "AcDbLine") (10 9389.1402714932
7873.3031674208 0.0) (11 8778.2805429864 7873.3031674208 0.0))
((0 . "LINE") (100 . "AcDbEntity") (8 . "SOLAR") (62 . 7) (370 . 13) (100 . "AcDbLine") (10 8778.2805429864
7873.3031674208 0.0) (11 8563.3484162896 8212.6696832579 0.0))
((0 . "LINE") (100 . "AcDbEntity") (8 . "SOLAR") (62 . 7) (370 . 13) (100 . "AcDbLine") (10 8602.6583710407
8178.7330316742 0.0) (11 8822.3981900452 8178.7330316742 0.0))
((0 . "LINE") (100 . "AcDbEntity") (8 . "SOLAR") (62 . 7) (370 . 13) (100 . "AcDbLine") (10 8822.3981900452
8178.7330316742 0.0) (11 9059.9547511312 8178.7330316742 0.0))
((0 . "LINE") (100 . "AcDbEntity") (8 . "SOLAR") (62 . 7) (370 . 13) (100 . "AcDbLine") (10 9059.9547511312
8178.7330316742 0.0) (11 9279.6945701357 8178.7330316742 0.0))
((0 . "LINE") (100 . "AcDbEntity") (8 . "SOLAR") (62 . 7) (370 . 13) (100 . "AcDbLine") (10 9279.6945701357
8178.7330316742 0.0) (11 9283.7754524887 8165.4977375566 0.0))
((0 . "LINE") (100 . "AcDbEntity") (8 . "SOLAR") (62 . 7) (370 . 13) (100 . "AcDbLine") (10 9283.7754524887
8165.4977375566 0.0) (11 9301.1715271493 8109.0780542986 0.0))
((0 . "LINE") (100 . "AcDbEntity") (8 . "SOLAR") (62 . 7) (370 . 13) (100 . "AcDbLine") (10 9301.1715271493
8109.0780542986 0.0) (11 9314.5913461538 8065.5542986425 0.0))
((0 . "LINE") (100 . "AcDbEntity") (8 . "SOLAR") (62 . 7) (370 . 13) (100 . "AcDbLine") (10 9314.5913461538
8065.5542986425 0.0) (11 9325.0289932127 8031.7024886878 0.0))
((0 . "LINE") (100 . "AcDbEntity") (8 . "SOLAR") (62 . 7) (370 . 13) (100 . "AcDbLine") (10 9325.0289932127
8031.7024886878 0.0) (11 9335.4666289593 7997.850678733 0.0))
((0 . "LINE") (100 . "AcDbEntity") (8 . "SOLAR") (62 . 7) (370 . 13) (100 . "AcDbLine") (10 9335.4666289593
7997.850678733 0.0) (11 9348.886459276 7954.3269230769 0.0))
((0 . "LINE") (100 . "AcDbEntity") (8 . "SOLAR") (62 . 7) (370 . 13) (100 . "AcDbLine") (10 9348.886459276
7954.3269230769 0.0) (11 9360.3181561086 7917.2511312217 0.0))
((0 . "LINE") (100 . "AcDbEntity") (8 . "SOLAR") (62 . 7) (370 . 13) (100 . "AcDbLine") (10 9360.3181561086
7917.2511312217 0.0) (11 9363.4049773756 7907.2398190045 0.0))
((0 . "LINE") (100 . "AcDbEntity") (8 . "SOLAR") (62 . 7) (370 . 13) (100 . "AcDbLine") (10 9363.4049773756
7907.2398190045 0.0) (11 9171.5686312217 7907.2398190045 0.0))
((0 . "LINE") (100 . "AcDbEntity") (8 . "SOLAR") (62 . 7) (370 . 13) (100 . "AcDbLine") (10 9171.5686312217
7907.2398190045 0.0) (11 8964.1779751131 7907.2398190045 0.0))
((0 . "LINE") (100 . "AcDbEntity") (8 . "SOLAR") (62 . 7) (370 . 13) (100 . "AcDbLine") (10 8964.1779751131
7907.2398190045 0.0) (11 8772.3416289593 7907.2398190045 0.0))
((0 . "LINE") (100 . "AcDbEntity") (8 . "SOLAR") (62 . 7) (370 . 13) (100 . "AcDbLine") (10 8772.3416289593
7907.2398190045 0.0) (11 8766.0845588235 7917.2511312217 0.0))
((0 . "LINE") (100 . "AcDbEntity") (8 . "SOLAR") (62 . 7) (370 . 13) (100 . "AcDbLine") (10 8766.0845588235
7917.2511312217 0.0) (11 8742.9121832579 7954.3269230769 0.0))
((0 . "LINE") (100 . "AcDbEntity") (8 . "SOLAR") (62 . 7) (370 . 13) (100 . "AcDbLine") (10 8742.9121832579
7954.3269230769 0.0) (11 8715.709841629 7997.850678733 0.0))
((0 . "LINE") (100 . "AcDbEntity") (8 . "SOLAR") (62 . 7) (370 . 13) (100 . "AcDbLine") (10 8715.709841629
7997.850678733 0.0) (11 8694.5524547511 8031.7024886878 0.0))
((0 . "LINE") (100 . "AcDbEntity") (8 . "SOLAR") (62 . 7) (370 . 13) (100 . "AcDbLine") (10 8694.5524547511
8031.7024886878 0.0) (11 8673.3950791855 8065.5542986425 0.0))
((0 . "LINE") (100 . "AcDbEntity") (8 . "SOLAR") (62 . 7) (370 . 13) (100 . "AcDbLine") (10 8673.3950791855
8065.5542986425 0.0) (11 8646.1927375566 8109.0780542986 0.0))
((0 . "LINE") (100 . "AcDbEntity") (8 . "SOLAR") (62 . 7) (370 . 13) (100 . "AcDbLine") (10 8646.1927375566
8109.0780542986 0.0) (11 8610.9304298643 8165.4977375566 0.0))
((0 . "LINE") (100 . "AcDbEntity") (8 . "SOLAR") (62 . 7) (370 . 13) (100 . "AcDbLine") (10 8610.9304298643
8165.4977375566 0.0) (11 8602.6583710407 8178.7330316742 0.0))
((0 . "LINE") (100 . "AcDbEntity") (8 . "SOLAR") (62 . 7) (370 . 13) (100 . "AcDbLine") (10 8822.3981900452
8178.7330316742 0.0) (11 8829.3099547511 8165.4977375566 0.0))
((0 . "LINE") (100 . "AcDbEntity") (8 . "SOLAR") (62 . 7) (370 . 13) (100 . "AcDbLine") (10 8829.3099547511
8165.4977375566 0.0) (11 8858.7735633484 8109.0780542986 0.0))
((0 . "LINE") (100 . "AcDbEntity") (8 . "SOLAR") (62 . 7) (370 . 13) (100 . "AcDbLine") (10 8858.7735633484
8109.0780542986 0.0) (11 8881.5026357466 8065.5542986425 0.0))
((0 . "LINE") (100 . "AcDbEntity") (8 . "SOLAR") (62 . 7) (370 . 13) (100 . "AcDbLine") (10 8881.5026357466
8065.5542986425 0.0) (11 8899.1808031674 8031.7024886878 0.0))
((0 . "LINE") (100 . "AcDbEntity") (8 . "SOLAR") (62 . 7) (370 . 13) (100 . "AcDbLine") (10 8899.1808031674
8031.7024886878 0.0) (11 8916.8589705882 7997.850678733 0.0))
((0 . "LINE") (100 . "AcDbEntity") (8 . "SOLAR") (62 . 7) (370 . 13) (100 . "AcDbLine") (10 8916.8589705882
7997.850678733 0.0) (11 8939.5880429864 7954.3269230769 0.0))
((0 . "LINE") (100 . "AcDbEntity") (8 . "SOLAR") (62 . 7) (370 . 13) (100 . "AcDbLine") (10 8939.5880429864
7954.3269230769 0.0) (11 8958.9498529412 7917.2511312217 0.0))
((0 . "LINE") (100 . "AcDbEntity") (8 . "SOLAR") (62 . 7) (370 . 13) (100 . "AcDbLine") (10 8958.9498529412
7917.2511312217 0.0) (11 8964.1779751131 7907.2398190045 0.0))
((0 . "LINE") (100 . "AcDbEntity") (8 . "SOLAR") (62 . 7) (370 . 13) (100 . "AcDbLine") (10 9059.9547511312
8178.7330316742 0.0) (11 9065.3959276018 8165.4977375566 0.0))
((0 . "LINE") (100 . "AcDbEntity") (8 . "SOLAR") (62 . 7) (370 . 13) (100 . "AcDbLine") (10 9065.3959276018
8165.4977375566 0.0) (11 9088.5906900453 8109.0780542986 0.0))
((0 . "LINE") (100 . "AcDbEntity") (8 . "SOLAR") (62 . 7) (370 . 13) (100 . "AcDbLine") (10 9088.5906900453
8109.0780542986 0.0) (11 9106.4837895928 8065.5542986425 0.0))
((0 . "LINE") (100 . "AcDbEntity") (8 . "SOLAR") (62 . 7) (370 . 13) (100 . "AcDbLine") (10 9106.4837895928
8065.5542986425 0.0) (11 9120.4006447964 8031.7024886878 0.0))
((0 . "LINE") (100 . "AcDbEntity") (8 . "SOLAR") (62 . 7) (370 . 13) (100 . "AcDbLine") (10 9120.4006447964
8031.7024886878 0.0) (11 9134.3175 7997.850678733 0.0))
((0 . "LINE") (100 . "AcDbEntity") (8 . "SOLAR") (62 . 7) (370 . 13) (100 . "AcDbLine") (10 9134.3175 7997.850678733
0.0) (11 9152.2105995475 7954.3269230769 0.0))
((0 . "LINE") (100 . "AcDbEntity") (8 . "SOLAR") (62 . 7) (370 . 13) (100 . "AcDbLine") (10 9152.2105995475
7954.3269230769 0.0) (11 9167.452861991 7917.2511312217 0.0))
((0 . "LINE") (100 . "AcDbEntity") (8 . "SOLAR") (62 . 7) (370 . 13) (100 . "AcDbLine") (10 9167.452861991
7917.2511312217 0.0) (11 9171.5686312217 7907.2398190045 0.0))
((0 . "LINE") (100 . "AcDbEntity") (8 . "SOLAR") (62 . 7) (370 . 13) (100 . "AcDbLine") (10 8610.9304298643
8165.4977375566 0.0) (11 8829.3099547511 8165.4977375566 0.0))
((0 . "LINE") (100 . "AcDbEntity") (8 . "SOLAR") (62 . 7) (370 . 13) (100 . "AcDbLine") (10 8829.3099547511
8165.4977375566 0.0) (11 9065.3959276018 8165.4977375566 0.0))
((0 . "LINE") (100 . "AcDbEntity") (8 . "SOLAR") (62 . 7) (370 . 13) (100 . "AcDbLine") (10 9065.3959276018
8165.4977375566 0.0) (11 9283.7754524887 8165.4977375566 0.0))
((0 . "LINE") (100 . "AcDbEntity") (8 . "SOLAR") (62 . 7) (370 . 13) (100 . "AcDbLine") (10 8646.1927375566
8109.0780542986 0.0) (11 8858.7735633484 8109.0780542986 0.0))
((0 . "LINE") (100 . "AcDbEntity") (8 . "SOLAR") (62 . 7) (370 . 13) (100 . "AcDbLine") (10 8858.7735633484
8109.0780542986 0.0) (11 9088.5906900453 8109.0780542986 0.0))
((0 . "LINE") (100 . "AcDbEntity") (8 . "SOLAR") (62 . 7) (370 . 13) (100 . "AcDbLine") (10 9088.5906900453
8109.0780542986 0.0) (11 9301.1715271493 8109.0780542986 0.0))
((0 . "LINE") (100 . "AcDbEntity") (8 . "SOLAR") (62 . 7) (370 . 13) (100 . "AcDbLine") (10 8673.3950791855
8065.5542986425 0.0) (11 8881.5026357466 8065.5542986425 0.0))
((0 . "LINE") (100 . "AcDbEntity") (8 . "SOLAR") (62 . 7) (370 . 13) (100 . "AcDbLine") (10 8881.5026357466
8065.5542986425 0.0) (11 9106.4837895928 8065.5542986425 0.0))
((0 . "LINE") (100 . "AcDbEntity") (8 . "SOLAR") (62 . 7) (370 . 13) (100 . "AcDbLine") (10 9106.4837895928
8065.5542986425 0.0) (11 9314.5913461538 8065.5542986425 0.0))
((0 . "LINE") (100 . "AcDbEntity") (8 . "SOLAR") (62 . 7) (370 . 13) (100 . "AcDbLine") (10 8694.5524547511
8031.7024886878 0.0) (11 8899.1808031674 8031.7024886878 0.0))
((0 . "LINE") (100 . "AcDbEntity") (8 . "SOLAR") (62 . 7) (370 . 13) (100 . "AcDbLine") (10 8899.1808031674
8031.7024886878 0.0) (11 9120.4006447964 8031.7024886878 0.0))
((0 . "LINE") (100 . "AcDbEntity") (8 . "SOLAR") (62 . 7) (370 . 13) (100 . "AcDbLine") (10 9120.4006447964
8031.7024886878 0.0) (11 9325.0289932127 8031.7024886878 0.0))
((0 . "LINE") (100 . "AcDbEntity") (8 . "SOLAR") (62 . 7) (370 . 13) (100 . "AcDbLine") (10 8715.709841629
7997.850678733 0.0) (11 8916.8589705882 7997.850678733 0.0))
((0 . "LINE") (100 . "AcDbEntity") (8 . "SOLAR") (62 . 7) (370 . 13) (100 . "AcDbLine") (10 8916.8589705882
7997.850678733 0.0) (11 9134.3175 7997.850678733 0.0))
((0 . "LINE") (100 . "AcDbEntity") (8 . "SOLAR") (62 . 7) (370 . 13) (100 . "AcDbLine") (10 9134.3175 7997.850678733
0.0) (11 9335.4666289593 7997.850678733 0.0))
((0 . "LINE") (100 . "AcDbEntity") (8 . "SOLAR") (62 . 7) (370 . 13) (100 . "AcDbLine") (10 8742.9121832579
7954.3269230769 0.0) (11 8939.5880429864 7954.3269230769 0.0))
((0 . "LINE") (100 . "AcDbEntity") (8 . "SOLAR") (62 . 7) (370 . 13) (100 . "AcDbLine") (10 8939.5880429864
7954.3269230769 0.0) (11 9152.2105995475 7954.3269230769 0.0))
((0 . "LINE") (100 . "AcDbEntity") (8 . "SOLAR") (62 . 7) (370 . 13) (100 . "AcDbLine") (10 9152.2105995475
7954.3269230769 0.0) (11 9348.886459276 7954.3269230769 0.0))
((0 . "LINE") (100 . "AcDbEntity") (8 . "SOLAR") (62 . 7) (370 . 13) (100 . "AcDbLine") (10 8766.0845588235
7917.2511312217 0.0) (11 8958.9498529412 7917.2511312217 0.0))
((0 . "LINE") (100 . "AcDbEntity") (8 . "SOLAR") (62 . 7) (370 . 13) (100 . "AcDbLine") (10 8958.9498529412
7917.2511312217 0.0) (11 9167.452861991 7917.2511312217 0.0))
((0 . "LINE") (100 . "AcDbEntity") (8 . "SOLAR") (62 . 7) (370 . 13) (100 . "AcDbLine") (10 9167.452861991
7917.2511312217 0.0) (11 9360.3181561086 7917.2511312217 0.0))
((0 . "LINE") (100 . "AcDbEntity") (8 . "SOLAR") (62 . 7) (370 . 13) (100 . "AcDbLine") (10 9332.5791855204
8212.6696832579 0.0) (11 9966.0633484163 8212.6696832579 0.0))
((0 . "LINE") (100 . "AcDbEntity") (8 . "SOLAR") (62 . 7) (370 . 13) (100 . "AcDbLine") (10 9966.0633484163
8212.6696832579 0.0) (11 9977.3755656109 7873.3031674208 0.0))
((0 . "LINE") (100 . "AcDbEntity") (8 . "SOLAR") (62 . 7) (370 . 13) (100 . "AcDbLine") (10 9977.3755656109
7873.3031674208 0.0) (11 9434.3891402715 7873.3031674208 0.0))
((0 . "LINE") (100 . "AcDbEntity") (8 . "SOLAR") (62 . 7) (370 . 13) (100 . "AcDbLine") (10 9434.3891402715
7873.3031674208 0.0) (11 9332.5791855204 8212.6696832579 0.0))
((0 . "LINE") (100 . "AcDbEntity") (8 . "SOLAR") (62 . 7) (370 . 13) (100 . "AcDbLine") (10 9358.371040724
8178.7330316742 0.0) (11 9550.9049773756 8178.7330316742 0.0))
((0 . "LINE") (100 . "AcDbEntity") (8 . "SOLAR") (62 . 7) (370 . 13) (100 . "AcDbLine") (10 9550.9049773756
8178.7330316742 0.0) (11 9759.0497737557 8178.7330316742 0.0))
((0 . "LINE") (100 . "AcDbEntity") (8 . "SOLAR") (62 . 7) (370 . 13) (100 . "AcDbLine") (10 9759.0497737557
8178.7330316742 0.0) (11 9951.5837104072 8178.7330316742 0.0))
((0 . "LINE") (100 . "AcDbEntity") (8 . "SOLAR") (62 . 7) (370 . 13) (100 . "AcDbLine") (10 9951.5837104072
8178.7330316742 0.0) (11 9952.1131221719 8165.4977375566 0.0))
((0 . "LINE") (100 . "AcDbEntity") (8 . "SOLAR") (62 . 7) (370 . 13) (100 . "AcDbLine") (10 9952.1131221719
8165.4977375566 0.0) (11 9954.3699095023 8109.0780542986 0.0))
((0 . "LINE") (100 . "AcDbEntity") (8 . "SOLAR") (62 . 7) (370 . 13) (100 . "AcDbLine") (10 9954.3699095023
8109.0780542986 0.0) (11 9956.1753393665 8063.9423076923 0.0))
((0 . "LINE") (100 . "AcDbEntity") (8 . "SOLAR") (62 . 7) (370 . 13) (100 . "AcDbLine") (10 9956.1753393665
8063.9423076923 0.0) (11 9957.4649321267 8031.7024886878 0.0))
((0 . "LINE") (100 . "AcDbEntity") (8 . "SOLAR") (62 . 7) (370 . 13) (100 . "AcDbLine") (10 9957.4649321267
8031.7024886878 0.0) (11 9958.8190045249 7997.850678733 0.0))
((0 . "LINE") (100 . "AcDbEntity") (8 . "SOLAR") (62 . 7) (370 . 13) (100 . "AcDbLine") (10 9958.8190045249
7997.850678733 0.0) (11 9960.5599547511 7954.3269230769 0.0))
((0 . "LINE") (100 . "AcDbEntity") (8 . "SOLAR") (62 . 7) (370 . 13) (100 . "AcDbLine") (10 9960.5599547511
7954.3269230769 0.0) (11 9962.0429864253 7917.2511312217 0.0))
((0 . "LINE") (100 . "AcDbEntity") (8 . "SOLAR") (62 . 7) (370 . 13) (100 . "AcDbLine") (10 9962.0429864253
7917.2511312217 0.0) (11 9962.443438914 7907.2398190045 0.0))
((0 . "LINE") (100 . "AcDbEntity") (8 . "SOLAR") (62 . 7) (370 . 13) (100 . "AcDbLine") (10 9962.443438914
7907.2398190045 0.0) (11 9792.2322737557 7907.2398190045 0.0))
((0 . "LINE") (100 . "AcDbEntity") (8 . "SOLAR") (62 . 7) (370 . 13) (100 . "AcDbLine") (10 9792.2322737557
7907.2398190045 0.0) (11 9608.2202149321 7907.2398190045 0.0))
((0 . "LINE") (100 . "AcDbEntity") (8 . "SOLAR") (62 . 7) (370 . 13) (100 . "AcDbLine") (10 9608.2202149321
7907.2398190045 0.0) (11 9438.0090497738 7907.2398190045 0.0))
((0 . "LINE") (100 . "AcDbEntity") (8 . "SOLAR") (62 . 7) (370 . 13) (100 . "AcDbLine") (10 9438.0090497738
7907.2398190045 0.0) (11 9435.07239819 7917.2511312217 0.0))
((0 . "LINE") (100 . "AcDbEntity") (8 . "SOLAR") (62 . 7) (370 . 13) (100 . "AcDbLine") (10 9435.07239819
7917.2511312217 0.0) (11 9424.1968325792 7954.3269230769 0.0))
((0 . "LINE") (100 . "AcDbEntity") (8 . "SOLAR") (62 . 7) (370 . 13) (100 . "AcDbLine") (10 9424.1968325792
7954.3269230769 0.0) (11 9411.4298642534 7997.850678733 0.0))
((0 . "LINE") (100 . "AcDbEntity") (8 . "SOLAR") (62 . 7) (370 . 13) (100 . "AcDbLine") (10 9411.4298642534
7997.850678733 0.0) (11 9401.5 8031.7024886878 0.0))
((0 . "LINE") (100 . "AcDbEntity") (8 . "SOLAR") (62 . 7) (370 . 13) (100 . "AcDbLine") (10 9401.5 8031.7024886878 0.0)
(11 9392.0429864253 8063.9423076923 0.0))
((0 . "LINE") (100 . "AcDbEntity") (8 . "SOLAR") (62 . 7) (370 . 13) (100 . "AcDbLine") (10 9392.0429864253
8063.9423076923 0.0) (11 9378.8031674208 8109.0780542986 0.0))
((0 . "LINE") (100 . "AcDbEntity") (8 . "SOLAR") (62 . 7) (370 . 13) (100 . "AcDbLine") (10 9378.8031674208
8109.0780542986 0.0) (11 9362.2533936652 8165.4977375566 0.0))
((0 . "LINE") (100 . "AcDbEntity") (8 . "SOLAR") (62 . 7) (370 . 13) (100 . "AcDbLine") (10 9362.2533936652
8165.4977375566 0.0) (11 9358.371040724 8178.7330316742 0.0))
((0 . "LINE") (100 . "AcDbEntity") (8 . "SOLAR") (62 . 7) (370 . 13) (100 . "AcDbLine") (10 9550.9049773756
8178.7330316742 0.0) (11 9553.6990950226 8165.4977375566 0.0))
((0 . "LINE") (100 . "AcDbEntity") (8 . "SOLAR") (62 . 7) (370 . 13) (100 . "AcDbLine") (10 9553.6990950226
8165.4977375566 0.0) (11 9565.6099208145 8109.0780542986 0.0))
((0 . "LINE") (100 . "AcDbEntity") (8 . "SOLAR") (62 . 7) (370 . 13) (100 . "AcDbLine") (10 9565.6099208145
8109.0780542986 0.0) (11 9575.1385746606 8063.9423076923 0.0))
((0 . "LINE") (100 . "AcDbEntity") (8 . "SOLAR") (62 . 7) (370 . 13) (100 . "AcDbLine") (10 9575.1385746606
8063.9423076923 0.0) (11 9581.9447624434 8031.7024886878 0.0))
((0 . "LINE") (100 . "AcDbEntity") (8 . "SOLAR") (62 . 7) (370 . 13) (100 . "AcDbLine") (10 9581.9447624434
8031.7024886878 0.0) (11 9589.0912556561 7997.850678733 0.0))
((0 . "LINE") (100 . "AcDbEntity") (8 . "SOLAR") (62 . 7) (370 . 13) (100 . "AcDbLine") (10 9589.0912556561
7997.850678733 0.0) (11 9598.2796040724 7954.3269230769 0.0))
((0 . "LINE") (100 . "AcDbEntity") (8 . "SOLAR") (62 . 7) (370 . 13) (100 . "AcDbLine") (10 9598.2796040724
7954.3269230769 0.0) (11 9606.1067081448 7917.2511312217 0.0))
((0 . "LINE") (100 . "AcDbEntity") (8 . "SOLAR") (62 . 7) (370 . 13) (100 . "AcDbLine") (10 9606.1067081448
7917.2511312217 0.0) (11 9608.2202149321 7907.2398190045 0.0))
((0 . "LINE") (100 . "AcDbEntity") (8 . "SOLAR") (62 . 7) (370 . 13) (100 . "AcDbLine") (10 9759.0497737557
8178.7330316742 0.0) (11 9760.6674208145 8165.4977375566 0.0))
((0 . "LINE") (100 . "AcDbEntity") (8 . "SOLAR") (62 . 7) (370 . 13) (100 . "AcDbLine") (10 9760.6674208145
8165.4977375566 0.0) (11 9767.5631561086 8109.0780542986 0.0))
((0 . "LINE") (100 . "AcDbEntity") (8 . "SOLAR") (62 . 7) (370 . 13) (100 . "AcDbLine") (10 9767.5631561086
8109.0780542986 0.0) (11 9773.0797511312 8063.9423076923 0.0))
((0 . "LINE") (100 . "AcDbEntity") (8 . "SOLAR") (62 . 7) (370 . 13) (100 . "AcDbLine") (10 9773.0797511312
8063.9423076923 0.0) (11 9777.0201696833 8031.7024886878 0.0))
((0 . "LINE") (100 . "AcDbEntity") (8 . "SOLAR") (62 . 7) (370 . 13) (100 . "AcDbLine") (10 9777.0201696833
8031.7024886878 0.0) (11 9781.1576131222 7997.850678733 0.0))
((0 . "LINE") (100 . "AcDbEntity") (8 . "SOLAR") (62 . 7) (370 . 13) (100 . "AcDbLine") (10 9781.1576131222
7997.850678733 0.0) (11 9786.4771832579 7954.3269230769 0.0))
((0 . "LINE") (100 . "AcDbEntity") (8 . "SOLAR") (62 . 7) (370 . 13) (100 . "AcDbLine") (10 9786.4771832579
7954.3269230769 0.0) (11 9791.0086764706 7917.2511312217 0.0))
((0 . "LINE") (100 . "AcDbEntity") (8 . "SOLAR") (62 . 7) (370 . 13) (100 . "AcDbLine") (10 9791.0086764706
7917.2511312217 0.0) (11 9792.2322737557 7907.2398190045 0.0))
((0 . "LINE") (100 . "AcDbEntity") (8 . "SOLAR") (62 . 7) (370 . 13) (100 . "AcDbLine") (10 9362.2533936652
8165.4977375566 0.0) (11 9553.6990950226 8165.4977375566 0.0))
((0 . "LINE") (100 . "AcDbEntity") (8 . "SOLAR") (62 . 7) (370 . 13) (100 . "AcDbLine") (10 9553.6990950226
8165.4977375566 0.0) (11 9760.6674208145 8165.4977375566 0.0))
((0 . "LINE") (100 . "AcDbEntity") (8 . "SOLAR") (62 . 7) (370 . 13) (100 . "AcDbLine") (10 9760.6674208145
8165.4977375566 0.0) (11 9952.1131221719 8165.4977375566 0.0))
((0 . "LINE") (100 . "AcDbEntity") (8 . "SOLAR") (62 . 7) (370 . 13) (100 . "AcDbLine") (10 9378.8031674208
8109.0780542986 0.0) (11 9565.6099208145 8109.0780542986 0.0))
((0 . "LINE") (100 . "AcDbEntity") (8 . "SOLAR") (62 . 7) (370 . 13) (100 . "AcDbLine") (10 9565.6099208145
8109.0780542986 0.0) (11 9767.5631561086 8109.0780542986 0.0))
((0 . "LINE") (100 . "AcDbEntity") (8 . "SOLAR") (62 . 7) (370 . 13) (100 . "AcDbLine") (10 9767.5631561086
8109.0780542986 0.0) (11 9954.3699095023 8109.0780542986 0.0))
((0 . "LINE") (100 . "AcDbEntity") (8 . "SOLAR") (62 . 7) (370 . 13) (100 . "AcDbLine") (10 9392.0429864253
8063.9423076923 0.0) (11 9575.1385746606 8063.9423076923 0.0))
((0 . "LINE") (100 . "AcDbEntity") (8 . "SOLAR") (62 . 7) (370 . 13) (100 . "AcDbLine") (10 9575.1385746606
8063.9423076923 0.0) (11 9773.0797511312 8063.9423076923 0.0))
((0 . "LINE") (100 . "AcDbEntity") (8 . "SOLAR") (62 . 7) (370 . 13) (100 . "AcDbLine") (10 9773.0797511312
8063.9423076923 0.0) (11 9956.1753393665 8063.9423076923 0.0))
((0 . "LINE") (100 . "AcDbEntity") (8 . "SOLAR") (62 . 7) (370 . 13) (100 . "AcDbLine") (10 9401.5 8031.7024886878 0.0)
(11 9581.9447624434 8031.7024886878 0.0))
((0 . "LINE") (100 . "AcDbEntity") (8 . "SOLAR") (62 . 7) (370 . 13) (100 . "AcDbLine") (10 9581.9447624434
8031.7024886878 0.0) (11 9777.0201696833 8031.7024886878 0.0))
((0 . "LINE") (100 . "AcDbEntity") (8 . "SOLAR") (62 . 7) (370 . 13) (100 . "AcDbLine") (10 9777.0201696833
8031.7024886878 0.0) (11 9957.4649321267 8031.7024886878 0.0))
((0 . "LINE") (100 . "AcDbEntity") (8 . "SOLAR") (62 . 7) (370 . 13) (100 . "AcDbLine") (10 9411.4298642534
7997.850678733 0.0) (11 9589.0912556561 7997.850678733 0.0))
((0 . "LINE") (100 . "AcDbEntity") (8 . "SOLAR") (62 . 7) (370 . 13) (100 . "AcDbLine") (10 9589.0912556561
7997.850678733 0.0) (11 9781.1576131222 7997.850678733 0.0))
((0 . "LINE") (100 . "AcDbEntity") (8 . "SOLAR") (62 . 7) (370 . 13) (100 . "AcDbLine") (10 9781.1576131222
7997.850678733 0.0) (11 9958.8190045249 7997.850678733 0.0))
((0 . "LINE") (100 . "AcDbEntity") (8 . "SOLAR") (62 . 7) (370 . 13) (100 . "AcDbLine") (10 9424.1968325792
7954.3269230769 0.0) (11 9598.2796040724 7954.3269230769 0.0))
((0 . "LINE") (100 . "AcDbEntity") (8 . "SOLAR") (62 . 7) (370 . 13) (100 . "AcDbLine") (10 9598.2796040724
7954.3269230769 0.0) (11 9786.4771832579 7954.3269230769 0.0))
((0 . "LINE") (100 . "AcDbEntity") (8 . "SOLAR") (62 . 7) (370 . 13) (100 . "AcDbLine") (10 9786.4771832579
7954.3269230769 0.0) (11 9960.5599547511 7954.3269230769 0.0))
((0 . "LINE") (100 . "AcDbEntity") (8 . "SOLAR") (62 . 7) (370 . 13) (100 . "AcDbLine") (10 9435.07239819
7917.2511312217 0.0) (11 9606.1067081448 7917.2511312217 0.0))
((0 . "LINE") (100 . "AcDbEntity") (8 . "SOLAR") (62 . 7) (370 . 13) (100 . "AcDbLine") (10 9606.1067081448
7917.2511312217 0.0) (11 9791.0086764706 7917.2511312217 0.0))
((0 . "LINE") (100 . "AcDbEntity") (8 . "SOLAR") (62 . 7) (370 . 13) (100 . "AcDbLine") (10 9791.0086764706
7917.2511312217 0.0) (11 9962.0429864253 7917.2511312217 0.0))
((0 . "LINE") (100 . "AcDbEntity") (8 . "SOLAR") (62 . 7) (370 . 13) (100 . "AcDbLine") (10 10022.6244343891
8212.6696832579 0.0) (11 10633.4841628959 8212.6696832579 0.0))
((0 . "LINE") (100 . "AcDbEntity") (8 . "SOLAR") (62 . 7) (370 . 13) (100 . "AcDbLine") (10 10633.4841628959
8212.6696832579 0.0) (11 10576.9230769231 7873.3031674208 0.0))
((0 . "LINE") (100 . "AcDbEntity") (8 . "SOLAR") (62 . 7) (370 . 13) (100 . "AcDbLine") (10 10576.9230769231
7873.3031674208 0.0) (11 10011.3122171946 7873.3031674208 0.0))
((0 . "LINE") (100 . "AcDbEntity") (8 . "SOLAR") (62 . 7) (370 . 13) (100 . "AcDbLine") (10 10011.3122171946
7873.3031674208 0.0) (11 10022.6244343891 8212.6696832579 0.0))
((0 . "LINE") (100 . "AcDbEntity") (8 . "SOLAR") (62 . 7) (370 . 13) (100 . "AcDbLine") (10 10036.6515837104
8178.7330316742 0.0) (11 10223.6048303167 8178.7330316742 0.0))
((0 . "LINE") (100 . "AcDbEntity") (8 . "SOLAR") (62 . 7) (370 . 13) (100 . "AcDbLine") (10 10223.6048303167
8178.7330316742 0.0) (11 10425.7164366516 8178.7330316742 0.0))
((0 . "LINE") (100 . "AcDbEntity") (8 . "SOLAR") (62 . 7) (370 . 13) (100 . "AcDbLine") (10 10425.7164366516
8178.7330316742 0.0) (11 10612.6696832579 8178.7330316742 0.0))
((0 . "LINE") (100 . "AcDbEntity") (8 . "SOLAR") (62 . 7) (370 . 13) (100 . "AcDbLine") (10 10612.6696832579
8178.7330316742 0.0) (11 10610.507918552 8165.4977375566 0.0))
((0 . "LINE") (100 . "AcDbEntity") (8 . "SOLAR") (62 . 7) (370 . 13) (100 . "AcDbLine") (10 10610.507918552
8165.4977375566 0.0) (11 10601.2927036199 8109.0780542986 0.0))
((0 . "LINE") (100 . "AcDbEntity") (8 . "SOLAR") (62 . 7) (370 . 13) (100 . "AcDbLine") (10 10601.2927036199
8109.0780542986 0.0) (11 10594.1838235294 8065.5542986425 0.0))
((0 . "LINE") (100 . "AcDbEntity") (8 . "SOLAR") (62 . 7) (370 . 13) (100 . "AcDbLine") (10 10594.1838235294
8065.5542986425 0.0) (11 10588.6546945701 8031.7024886878 0.0))
((0 . "LINE") (100 . "AcDbEntity") (8 . "SOLAR") (62 . 7) (370 . 13) (100 . "AcDbLine") (10 10588.6546945701
8031.7024886878 0.0) (11 10583.1255656109 7997.850678733 0.0))
((0 . "LINE") (100 . "AcDbEntity") (8 . "SOLAR") (62 . 7) (370 . 13) (100 . "AcDbLine") (10 10583.1255656109
7997.850678733 0.0) (11 10576.0166855204 7954.3269230769 0.0))
((0 . "LINE") (100 . "AcDbEntity") (8 . "SOLAR") (62 . 7) (370 . 13) (100 . "AcDbLine") (10 10576.0166855204
7954.3269230769 0.0) (11 10569.9609728507 7917.2511312217 0.0))
((0 . "LINE") (100 . "AcDbEntity") (8 . "SOLAR") (62 . 7) (370 . 13) (100 . "AcDbLine") (10 10569.9609728507
7917.2511312217 0.0) (11 10568.3257918552 7907.2398190045 0.0))
((0 . "LINE") (100 . "AcDbEntity") (8 . "SOLAR") (62 . 7) (370 . 13) (100 . "AcDbLine") (10 10568.3257918552
7907.2398190045 0.0) (11 10392.5339366516 7907.2398190045 0.0))
((0 . "LINE") (100 . "AcDbEntity") (8 . "SOLAR") (62 . 7) (370 . 13) (100 . "AcDbLine") (10 10392.5339366516
7907.2398190045 0.0) (11 10202.4886877828 7907.2398190045 0.0))
((0 . "LINE") (100 . "AcDbEntity") (8 . "SOLAR") (62 . 7) (370 . 13) (100 . "AcDbLine") (10 10202.4886877828
7907.2398190045 0.0) (11 10026.6968325792 7907.2398190045 0.0))
((0 . "LINE") (100 . "AcDbEntity") (8 . "SOLAR") (62 . 7) (370 . 13) (100 . "AcDbLine") (10 10026.6968325792
7907.2398190045 0.0) (11 10027.0639140272 7917.2511312217 0.0))
((0 . "LINE") (100 . "AcDbEntity") (8 . "SOLAR") (62 . 7) (370 . 13) (100 . "AcDbLine") (10 10027.0639140272
7917.2511312217 0.0) (11 10028.4233597285 7954.3269230769 0.0))
((0 . "LINE") (100 . "AcDbEntity") (8 . "SOLAR") (62 . 7) (370 . 13) (100 . "AcDbLine") (10 10028.4233597285
7954.3269230769 0.0) (11 10030.0192307692 7997.850678733 0.0))
((0 . "LINE") (100 . "AcDbEntity") (8 . "SOLAR") (62 . 7) (370 . 13) (100 . "AcDbLine") (10 10030.0192307692
7997.850678733 0.0) (11 10031.2604638009 8031.7024886878 0.0))
((0 . "LINE") (100 . "AcDbEntity") (8 . "SOLAR") (62 . 7) (370 . 13) (100 . "AcDbLine") (10 10031.2604638009
8031.7024886878 0.0) (11 10032.5016968326 8065.5542986425 0.0))
((0 . "LINE") (100 . "AcDbEntity") (8 . "SOLAR") (62 . 7) (370 . 13) (100 . "AcDbLine") (10 10032.5016968326
8065.5542986425 0.0) (11 10034.0975678733 8109.0780542986 0.0))
((0 . "LINE") (100 . "AcDbEntity") (8 . "SOLAR") (62 . 7) (370 . 13) (100 . "AcDbLine") (10 10034.0975678733
8109.0780542986 0.0) (11 10036.1662895928 8165.4977375566 0.0))
((0 . "LINE") (100 . "AcDbEntity") (8 . "SOLAR") (62 . 7) (370 . 13) (100 . "AcDbLine") (10 10036.1662895928
8165.4977375566 0.0) (11 10036.6515837104 8178.7330316742 0.0))
((0 . "LINE") (100 . "AcDbEntity") (8 . "SOLAR") (62 . 7) (370 . 13) (100 . "AcDbLine") (10 10223.6048303167
8178.7330316742 0.0) (11 10222.575418552 8165.4977375566 0.0))
((0 . "LINE") (100 . "AcDbEntity") (8 . "SOLAR") (62 . 7) (370 . 13) (100 . "AcDbLine") (10 10222.575418552
8165.4977375566 0.0) (11 10218.1872171946 8109.0780542986 0.0))
((0 . "LINE") (100 . "AcDbEntity") (8 . "SOLAR") (62 . 7) (370 . 13) (100 . "AcDbLine") (10 10218.1872171946
8109.0780542986 0.0) (11 10214.8020361991 8065.5542986425 0.0))
((0 . "LINE") (100 . "AcDbEntity") (8 . "SOLAR") (62 . 7) (370 . 13) (100 . "AcDbLine") (10 10214.8020361991
8065.5542986425 0.0) (11 10212.1691176471 8031.7024886878 0.0))
((0 . "LINE") (100 . "AcDbEntity") (8 . "SOLAR") (62 . 7) (370 . 13) (100 . "AcDbLine") (10 10212.1691176471
8031.7024886878 0.0) (11 10209.536199095 7997.850678733 0.0))
((0 . "LINE") (100 . "AcDbEntity") (8 . "SOLAR") (62 . 7) (370 . 13) (100 . "AcDbLine") (10 10209.536199095
7997.850678733 0.0) (11 10206.1510180995 7954.3269230769 0.0))
((0 . "LINE") (100 . "AcDbEntity") (8 . "SOLAR") (62 . 7) (370 . 13) (100 . "AcDbLine") (10 10206.1510180995
7954.3269230769 0.0) (11 10203.267341629 7917.2511312217 0.0))
((0 . "LINE") (100 . "AcDbEntity") (8 . "SOLAR") (62 . 7) (370 . 13) (100 . "AcDbLine") (10 10203.267341629
7917.2511312217 0.0) (11 10202.4886877828 7907.2398190045 0.0))
((0 . "LINE") (100 . "AcDbEntity") (8 . "SOLAR") (62 . 7) (370 . 13) (100 . "AcDbLine") (10 10425.7164366516
8178.7330316742 0.0) (11 10424.0987895928 8165.4977375566 0.0))
((0 . "LINE") (100 . "AcDbEntity") (8 . "SOLAR") (62 . 7) (370 . 13) (100 . "AcDbLine") (10 10424.0987895928
8165.4977375566 0.0) (11 10417.2030542986 8109.0780542986 0.0))
((0 . "LINE") (100 . "AcDbEntity") (8 . "SOLAR") (62 . 7) (370 . 13) (100 . "AcDbLine") (10 10417.2030542986
8109.0780542986 0.0) (11 10411.8834841629 8065.5542986425 0.0))
((0 . "LINE") (100 . "AcDbEntity") (8 . "SOLAR") (62 . 7) (370 . 13) (100 . "AcDbLine") (10 10411.8834841629
8065.5542986425 0.0) (11 10407.746040724 8031.7024886878 0.0))
((0 . "LINE") (100 . "AcDbEntity") (8 . "SOLAR") (62 . 7) (370 . 13) (100 . "AcDbLine") (10 10407.746040724
8031.7024886878 0.0) (11 10403.6085972851 7997.850678733 0.0))
((0 . "LINE") (100 . "AcDbEntity") (8 . "SOLAR") (62 . 7) (370 . 13) (100 . "AcDbLine") (10 10403.6085972851
7997.850678733 0.0) (11 10398.2890271493 7954.3269230769 0.0))
((0 . "LINE") (100 . "AcDbEntity") (8 . "SOLAR") (62 . 7) (370 . 13) (100 . "AcDbLine") (10 10398.2890271493
7954.3269230769 0.0) (11 10393.7575452489 7917.2511312217 0.0))
((0 . "LINE") (100 . "AcDbEntity") (8 . "SOLAR") (62 . 7) (370 . 13) (100 . "AcDbLine") (10 10393.7575452489
7917.2511312217 0.0) (11 10392.5339366516 7907.2398190045 0.0))
((0 . "LINE") (100 . "AcDbEntity") (8 . "SOLAR") (62 . 7) (370 . 13) (100 . "AcDbLine") (10 10036.1662895928
8165.4977375566 0.0) (11 10222.575418552 8165.4977375566 0.0))
((0 . "LINE") (100 . "AcDbEntity") (8 . "SOLAR") (62 . 7) (370 . 13) (100 . "AcDbLine") (10 10222.575418552
8165.4977375566 0.0) (11 10424.0987895928 8165.4977375566 0.0))
((0 . "LINE") (100 . "AcDbEntity") (8 . "SOLAR") (62 . 7) (370 . 13) (100 . "AcDbLine") (10 10424.0987895928
8165.4977375566 0.0) (11 10610.507918552 8165.4977375566 0.0))
((0 . "LINE") (100 . "AcDbEntity") (8 . "SOLAR") (62 . 7) (370 . 13) (100 . "AcDbLine") (10 10034.0975678733
8109.0780542986 0.0) (11 10218.1872171946 8109.0780542986 0.0))
((0 . "LINE") (100 . "AcDbEntity") (8 . "SOLAR") (62 . 7) (370 . 13) (100 . "AcDbLine") (10 10218.1872171946
8109.0780542986 0.0) (11 10417.2030542986 8109.0780542986 0.0))
((0 . "LINE") (100 . "AcDbEntity") (8 . "SOLAR") (62 . 7) (370 . 13) (100 . "AcDbLine") (10 10417.2030542986
8109.0780542986 0.0) (11 10601.2927036199 8109.0780542986 0.0))
((0 . "LINE") (100 . "AcDbEntity") (8 . "SOLAR") (62 . 7) (370 . 13) (100 . "AcDbLine") (10 10032.5016968326
8065.5542986425 0.0) (11 10214.8020361991 8065.5542986425 0.0))
((0 . "LINE") (100 . "AcDbEntity") (8 . "SOLAR") (62 . 7) (370 . 13) (100 . "AcDbLine") (10 10214.8020361991
8065.5542986425 0.0) (11 10411.8834841629 8065.5542986425 0.0))
((0 . "LINE") (100 . "AcDbEntity") (8 . "SOLAR") (62 . 7) (370 . 13) (100 . "AcDbLine") (10 10411.8834841629
8065.5542986425 0.0) (11 10594.1838235294 8065.5542986425 0.0))
((0 . "LINE") (100 . "AcDbEntity") (8 . "SOLAR") (62 . 7) (370 . 13) (100 . "AcDbLine") (10 10031.2604638009
8031.7024886878 0.0) (11 10212.1691176471 8031.7024886878 0.0))
((0 . "LINE") (100 . "AcDbEntity") (8 . "SOLAR") (62 . 7) (370 . 13) (100 . "AcDbLine") (10 10212.1691176471
8031.7024886878 0.0) (11 10407.746040724 8031.7024886878 0.0))
((0 . "LINE") (100 . "AcDbEntity") (8 . "SOLAR") (62 . 7) (370 . 13) (100 . "AcDbLine") (10 10407.746040724
8031.7024886878 0.0) (11 10588.6546945701 8031.7024886878 0.0))
((0 . "LINE") (100 . "AcDbEntity") (8 . "SOLAR") (62 . 7) (370 . 13) (100 . "AcDbLine") (10 10030.0192307692
7997.850678733 0.0) (11 10209.536199095 7997.850678733 0.0))
((0 . "LINE") (100 . "AcDbEntity") (8 . "SOLAR") (62 . 7) (370 . 13) (100 . "AcDbLine") (10 10209.536199095
7997.850678733 0.0) (11 10403.6085972851 7997.850678733 0.0))
((0 . "LINE") (100 . "AcDbEntity") (8 . "SOLAR") (62 . 7) (370 . 13) (100 . "AcDbLine") (10 10403.6085972851
7997.850678733 0.0) (11 10583.1255656109 7997.850678733 0.0))
((0 . "LINE") (100 . "AcDbEntity") (8 . "SOLAR") (62 . 7) (370 . 13) (100 . "AcDbLine") (10 10028.4233597285
7954.3269230769 0.0) (11 10206.1510180995 7954.3269230769 0.0))
((0 . "LINE") (100 . "AcDbEntity") (8 . "SOLAR") (62 . 7) (370 . 13) (100 . "AcDbLine") (10 10206.1510180995
7954.3269230769 0.0) (11 10398.2890271493 7954.3269230769 0.0))
((0 . "LINE") (100 . "AcDbEntity") (8 . "SOLAR") (62 . 7) (370 . 13) (100 . "AcDbLine") (10 10398.2890271493
7954.3269230769 0.0) (11 10576.0166855204 7954.3269230769 0.0))
((0 . "LINE") (100 . "AcDbEntity") (8 . "SOLAR") (62 . 7) (370 . 13) (100 . "AcDbLine") (10 10027.0639140272
7917.2511312217 0.0) (11 10203.267341629 7917.2511312217 0.0))
((0 . "LINE") (100 . "AcDbEntity") (8 . "SOLAR") (62 . 7) (370 . 13) (100 . "AcDbLine") (10 10203.267341629
7917.2511312217 0.0) (11 10393.7575452489 7917.2511312217 0.0))
((0 . "LINE") (100 . "AcDbEntity") (8 . "SOLAR") (62 . 7) (370 . 13) (100 . "AcDbLine") (10 10393.7575452489
7917.2511312217 0.0) (11 10569.9609728507 7917.2511312217 0.0))
((0 . "LINE") (100 . "AcDbEntity") (8 . "SOLAR") (62 . 7) (370 . 13) (100 . "AcDbLine") (10 10667.4208144796
8212.6696832579 0.0) (11 11300.9049773756 8212.6696832579 0.0))
((0 . "LINE") (100 . "AcDbEntity") (8 . "SOLAR") (62 . 7) (370 . 13) (100 . "AcDbLine") (10 11300.9049773756
8212.6696832579 0.0) (11 11153.8461538462 7873.3031674208 0.0))
((0 . "LINE") (100 . "AcDbEntity") (8 . "SOLAR") (62 . 7) (370 . 13) (100 . "AcDbLine") (10 11153.8461538462
7873.3031674208 0.0) (11 10622.1719457014 7873.3031674208 0.0))
((0 . "LINE") (100 . "AcDbEntity") (8 . "SOLAR") (62 . 7) (370 . 13) (100 . "AcDbLine") (10 10622.1719457014
7873.3031674208 0.0) (11 10667.4208144796 8212.6696832579 0.0))
((0 . "LINE") (100 . "AcDbEntity") (8 . "SOLAR") (62 . 7) (370 . 13) (100 . "AcDbLine") (10 10678.4785067873
8178.7330316742 0.0) (11 10870.6636538462 8178.7330316742 0.0))
((0 . "LINE") (100 . "AcDbEntity") (8 . "SOLAR") (62 . 7) (370 . 13) (100 . "AcDbLine") (10 10870.6636538462
8178.7330316742 0.0) (11 11078.4313687783 8178.7330316742 0.0))
((0 . "LINE") (100 . "AcDbEntity") (8 . "SOLAR") (62 . 7) (370 . 13) (100 . "AcDbLine") (10 11078.4313687783
8178.7330316742 0.0) (11 11270.6165158371 8178.7330316742 0.0))
((0 . "LINE") (100 . "AcDbEntity") (8 . "SOLAR") (62 . 7) (370 . 13) (100 . "AcDbLine") (10 11270.6165158371
8178.7330316742 0.0) (11 11264.9804864253 8165.4977375566 0.0))
((0 . "LINE") (100 . "AcDbEntity") (8 . "SOLAR") (62 . 7) (370 . 13) (100 . "AcDbLine") (10 11264.9804864253
8165.4977375566 0.0) (11 11240.95510181 8109.0780542986 0.0))
((0 . "LINE") (100 . "AcDbEntity") (8 . "SOLAR") (62 . 7) (370 . 13) (100 . "AcDbLine") (10 11240.95510181
8109.0780542986 0.0) (11 11221.7347963801 8063.9423076923 0.0))
((0 . "LINE") (100 . "AcDbEntity") (8 . "SOLAR") (62 . 7) (370 . 13) (100 . "AcDbLine") (10 11221.7347963801
8063.9423076923 0.0) (11 11208.0060067873 8031.7024886878 0.0))
((0 . "LINE") (100 . "AcDbEntity") (8 . "SOLAR") (62 . 7) (370 . 13) (100 . "AcDbLine") (10 11208.0060067873
8031.7024886878 0.0) (11 11193.590780543 7997.850678733 0.0))
((0 . "LINE") (100 . "AcDbEntity") (8 . "SOLAR") (62 . 7) (370 . 13) (100 . "AcDbLine") (10 11193.590780543
7997.850678733 0.0) (11 11175.0569117647 7954.3269230769 0.0))
((0 . "LINE") (100 . "AcDbEntity") (8 . "SOLAR") (62 . 7) (370 . 13) (100 . "AcDbLine") (10 11175.0569117647
7954.3269230769 0.0) (11 11159.268800905 7917.2511312217 0.0))
((0 . "LINE") (100 . "AcDbEntity") (8 . "SOLAR") (62 . 7) (370 . 13) (100 . "AcDbLine") (10 11159.268800905
7917.2511312217 0.0) (11 11155.0056561086 7907.2398190045 0.0))
((0 . "LINE") (100 . "AcDbEntity") (8 . "SOLAR") (62 . 7) (370 . 13) (100 . "AcDbLine") (10 11155.0056561086
7907.2398190045 0.0) (11 10987.9336312217 7907.2398190045 0.0))
((0 . "LINE") (100 . "AcDbEntity") (8 . "SOLAR") (62 . 7) (370 . 13) (100 . "AcDbLine") (10 10987.9336312217
7907.2398190045 0.0) (11 10807.3152375566 7907.2398190045 0.0))
((0 . "LINE") (100 . "AcDbEntity") (8 . "SOLAR") (62 . 7) (370 . 13) (100 . "AcDbLine") (10 10807.3152375566
7907.2398190045 0.0) (11 10640.2432126697 7907.2398190045 0.0))
((0 . "LINE") (100 . "AcDbEntity") (8 . "SOLAR") (62 . 7) (370 . 13) (100 . "AcDbLine") (10 10640.2432126697
7907.2398190045 0.0) (11 10641.6531334842 7917.2511312217 0.0))
((0 . "LINE") (100 . "AcDbEntity") (8 . "SOLAR") (62 . 7) (370 . 13) (100 . "AcDbLine") (10 10641.6531334842
7917.2511312217 0.0) (11 10646.8746493213 7954.3269230769 0.0))
((0 . "LINE") (100 . "AcDbEntity") (8 . "SOLAR") (62 . 7) (370 . 13) (100 . "AcDbLine") (10 10646.8746493213
7954.3269230769 0.0) (11 10653.0042420814 7997.850678733 0.0))
((0 . "LINE") (100 . "AcDbEntity") (8 . "SOLAR") (62 . 7) (370 . 13) (100 . "AcDbLine") (10 10653.0042420814
7997.850678733 0.0) (11 10657.7717081448 8031.7024886878 0.0))
((0 . "LINE") (100 . "AcDbEntity") (8 . "SOLAR") (62 . 7) (370 . 13) (100 . "AcDbLine") (10 10657.7717081448
8031.7024886878 0.0) (11 10662.3121493213 8063.9423076923 0.0))
((0 . "LINE") (100 . "AcDbEntity") (8 . "SOLAR") (62 . 7) (370 . 13) (100 . "AcDbLine") (10 10662.3121493213
8063.9423076923 0.0) (11 10668.6687669683 8109.0780542986 0.0))
((0 . "LINE") (100 . "AcDbEntity") (8 . "SOLAR") (62 . 7) (370 . 13) (100 . "AcDbLine") (10 10668.6687669683
8109.0780542986 0.0) (11 10676.6145361991 8165.4977375566 0.0))
((0 . "LINE") (100 . "AcDbEntity") (8 . "SOLAR") (62 . 7) (370 . 13) (100 . "AcDbLine") (10 10676.6145361991
8165.4977375566 0.0) (11 10678.4785067873 8178.7330316742 0.0))
((0 . "LINE") (100 . "AcDbEntity") (8 . "SOLAR") (62 . 7) (370 . 13) (100 . "AcDbLine") (10 10870.6636538462
8178.7330316742 0.0) (11 10867.575418552 8165.4977375566 0.0))
((0 . "LINE") (100 . "AcDbEntity") (8 . "SOLAR") (62 . 7) (370 . 13) (100 . "AcDbLine") (10 10867.575418552
8165.4977375566 0.0) (11 10854.4108257919 8109.0780542986 0.0))
((0 . "LINE") (100 . "AcDbEntity") (8 . "SOLAR") (62 . 7) (370 . 13) (100 . "AcDbLine") (10 10854.4108257919
8109.0780542986 0.0) (11 10843.8791515837 8063.9423076923 0.0))
((0 . "LINE") (100 . "AcDbEntity") (8 . "SOLAR") (62 . 7) (370 . 13) (100 . "AcDbLine") (10 10843.8791515837
8063.9423076923 0.0) (11 10836.3565271493 8031.7024886878 0.0))
((0 . "LINE") (100 . "AcDbEntity") (8 . "SOLAR") (62 . 7) (370 . 13) (100 . "AcDbLine") (10 10836.3565271493
8031.7024886878 0.0) (11 10828.4577714932 7997.850678733 0.0))
((0 . "LINE") (100 . "AcDbEntity") (8 . "SOLAR") (62 . 7) (370 . 13) (100 . "AcDbLine") (10 10828.4577714932
7997.850678733 0.0) (11 10818.3022285068 7954.3269230769 0.0))
((0 . "LINE") (100 . "AcDbEntity") (8 . "SOLAR") (62 . 7) (370 . 13) (100 . "AcDbLine") (10 10818.3022285068
7954.3269230769 0.0) (11 10809.6512104072 7917.2511312217 0.0))
((0 . "LINE") (100 . "AcDbEntity") (8 . "SOLAR") (62 . 7) (370 . 13) (100 . "AcDbLine") (10 10809.6512104072
7917.2511312217 0.0) (11 10807.3152375566 7907.2398190045 0.0))
((0 . "LINE") (100 . "AcDbEntity") (8 . "SOLAR") (62 . 7) (370 . 13) (100 . "AcDbLine") (10 11078.4313687783
8178.7330316742 0.0) (11 11074.0196040724 8165.4977375566 0.0))
((0 . "LINE") (100 . "AcDbEntity") (8 . "SOLAR") (62 . 7) (370 . 13) (100 . "AcDbLine") (10 11074.0196040724
8165.4977375566 0.0) (11 11055.2130429864 8109.0780542986 0.0))
((0 . "LINE") (100 . "AcDbEntity") (8 . "SOLAR") (62 . 7) (370 . 13) (100 . "AcDbLine") (10 11055.2130429864
8109.0780542986 0.0) (11 11040.1677941176 8063.9423076923 0.0))
((0 . "LINE") (100 . "AcDbEntity") (8 . "SOLAR") (62 . 7) (370 . 13) (100 . "AcDbLine") (10 11040.1677941176
8063.9423076923 0.0) (11 11029.4211877828 8031.7024886878 0.0))
((0 . "LINE") (100 . "AcDbEntity") (8 . "SOLAR") (62 . 7) (370 . 13) (100 . "AcDbLine") (10 11029.4211877828
8031.7024886878 0.0) (11 11018.1372511312 7997.850678733 0.0))
((0 . "LINE") (100 . "AcDbEntity") (8 . "SOLAR") (62 . 7) (370 . 13) (100 . "AcDbLine") (10 11018.1372511312
7997.850678733 0.0) (11 11003.6293325792 7954.3269230769 0.0))
((0 . "LINE") (100 . "AcDbEntity") (8 . "SOLAR") (62 . 7) (370 . 13) (100 . "AcDbLine") (10 11003.6293325792
7954.3269230769 0.0) (11 10991.2707352941 7917.2511312217 0.0))
((0 . "LINE") (100 . "AcDbEntity") (8 . "SOLAR") (62 . 7) (370 . 13) (100 . "AcDbLine") (10 10991.2707352941
7917.2511312217 0.0) (11 10987.9336312217 7907.2398190045 0.0))
((0 . "LINE") (100 . "AcDbEntity") (8 . "SOLAR") (62 . 7) (370 . 13) (100 . "AcDbLine") (10 10676.6145361991
8165.4977375566 0.0) (11 10867.575418552 8165.4977375566 0.0))
((0 . "LINE") (100 . "AcDbEntity") (8 . "SOLAR") (62 . 7) (370 . 13) (100 . "AcDbLine") (10 10867.575418552
8165.4977375566 0.0) (11 11074.0196040724 8165.4977375566 0.0))
((0 . "LINE") (100 . "AcDbEntity") (8 . "SOLAR") (62 . 7) (370 . 13) (100 . "AcDbLine") (10 11074.0196040724
8165.4977375566 0.0) (11 11264.9804864253 8165.4977375566 0.0))
((0 . "LINE") (100 . "AcDbEntity") (8 . "SOLAR") (62 . 7) (370 . 13) (100 . "AcDbLine") (10 10668.6687669683
8109.0780542986 0.0) (11 10854.4108257919 8109.0780542986 0.0))
((0 . "LINE") (100 . "AcDbEntity") (8 . "SOLAR") (62 . 7) (370 . 13) (100 . "AcDbLine") (10 10854.4108257919
8109.0780542986 0.0) (11 11055.2130429864 8109.0780542986 0.0))
((0 . "LINE") (100 . "AcDbEntity") (8 . "SOLAR") (62 . 7) (370 . 13) (100 . "AcDbLine") (10 11055.2130429864
8109.0780542986 0.0) (11 11240.95510181 8109.0780542986 0.0))
((0 . "LINE") (100 . "AcDbEntity") (8 . "SOLAR") (62 . 7) (370 . 13) (100 . "AcDbLine") (10 10662.3121493213
8063.9423076923 0.0) (11 10843.8791515837 8063.9423076923 0.0))
((0 . "LINE") (100 . "AcDbEntity") (8 . "SOLAR") (62 . 7) (370 . 13) (100 . "AcDbLine") (10 10843.8791515837
8063.9423076923 0.0) (11 11040.1677941176 8063.9423076923 0.0))
((0 . "LINE") (100 . "AcDbEntity") (8 . "SOLAR") (62 . 7) (370 . 13) (100 . "AcDbLine") (10 11040.1677941176
8063.9423076923 0.0) (11 11221.7347963801 8063.9423076923 0.0))
((0 . "LINE") (100 . "AcDbEntity") (8 . "SOLAR") (62 . 7) (370 . 13) (100 . "AcDbLine") (10 10657.7717081448
8031.7024886878 0.0) (11 10836.3565271493 8031.7024886878 0.0))
((0 . "LINE") (100 . "AcDbEntity") (8 . "SOLAR") (62 . 7) (370 . 13) (100 . "AcDbLine") (10 10836.3565271493
8031.7024886878 0.0) (11 11029.4211877828 8031.7024886878 0.0))
((0 . "LINE") (100 . "AcDbEntity") (8 . "SOLAR") (62 . 7) (370 . 13) (100 . "AcDbLine") (10 11029.4211877828
8031.7024886878 0.0) (11 11208.0060067873 8031.7024886878 0.0))
((0 . "LINE") (100 . "AcDbEntity") (8 . "SOLAR") (62 . 7) (370 . 13) (100 . "AcDbLine") (10 10653.0042420814
7997.850678733 0.0) (11 10828.4577714932 7997.850678733 0.0))
((0 . "LINE") (100 . "AcDbEntity") (8 . "SOLAR") (62 . 7) (370 . 13) (100 . "AcDbLine") (10 10828.4577714932
7997.850678733 0.0) (11 11018.1372511312 7997.850678733 0.0))
((0 . "LINE") (100 . "AcDbEntity") (8 . "SOLAR") (62 . 7) (370 . 13) (100 . "AcDbLine") (10 11018.1372511312
7997.850678733 0.0) (11 11193.590780543 7997.850678733 0.0))
((0 . "LINE") (100 . "AcDbEntity") (8 . "SOLAR") (62 . 7) (370 . 13) (100 . "AcDbLine") (10 10646.8746493213
7954.3269230769 0.0) (11 10818.3022285068 7954.3269230769 0.0))
((0 . "LINE") (100 . "AcDbEntity") (8 . "SOLAR") (62 . 7) (370 . 13) (100 . "AcDbLine") (10 10818.3022285068
7954.3269230769 0.0) (11 11003.6293325792 7954.3269230769 0.0))
((0 . "LINE") (100 . "AcDbEntity") (8 . "SOLAR") (62 . 7) (370 . 13) (100 . "AcDbLine") (10 11003.6293325792
7954.3269230769 0.0) (11 11175.0569117647 7954.3269230769 0.0))
((0 . "LINE") (100 . "AcDbEntity") (8 . "SOLAR") (62 . 7) (370 . 13) (100 . "AcDbLine") (10 10641.6531334842
7917.2511312217 0.0) (11 10809.6512104072 7917.2511312217 0.0))
((0 . "LINE") (100 . "AcDbEntity") (8 . "SOLAR") (62 . 7) (370 . 13) (100 . "AcDbLine") (10 10809.6512104072
7917.2511312217 0.0) (11 10991.2707352941 7917.2511312217 0.0))
((0 . "LINE") (100 . "AcDbEntity") (8 . "SOLAR") (62 . 7) (370 . 13) (100 . "AcDbLine") (10 10991.2707352941
7917.2511312217 0.0) (11 11159.268800905 7917.2511312217 0.0))
((0 . "LINE") (100 . "AcDbEntity") (8 . "SOLAR") (62 . 7) (370 . 13) (100 . "AcDbLine") (10 11346.1538461538
8212.6696832579 0.0) (11 12149.3212669683 8212.6696832579 0.0))
((0 . "LINE") (100 . "AcDbEntity") (8 . "SOLAR") (62 . 7) (370 . 13) (100 . "AcDbLine") (10 12149.3212669683
8212.6696832579 0.0) (11 11945.7013574661 7873.3031674208 0.0))
((0 . "LINE") (100 . "AcDbEntity") (8 . "SOLAR") (62 . 7) (370 . 13) (100 . "AcDbLine") (10 11945.7013574661
7873.3031674208 0.0) (11 11199.0950226244 7873.3031674208 0.0))
((0 . "LINE") (100 . "AcDbEntity") (8 . "SOLAR") (62 . 7) (370 . 13) (100 . "AcDbLine") (10 11199.0950226244
7873.3031674208 0.0) (11 11346.1538461538 8212.6696832579 0.0))
((0 . "LINE") (100 . "AcDbEntity") (8 . "SOLAR") (62 . 7) (370 . 13) (100 . "AcDbLine") (10 11351.3857466063
8178.7330316742 0.0) (11 11597.2850678733 8178.7330316742 0.0))
((0 . "LINE") (100 . "AcDbEntity") (8 . "SOLAR") (62 . 7) (370 . 13) (100 . "AcDbLine") (10 11597.2850678733
8178.7330316742 0.0) (11 11863.1221719457 8178.7330316742 0.0))
((0 . "LINE") (100 . "AcDbEntity") (8 . "SOLAR") (62 . 7) (370 . 13) (100 . "AcDbLine") (10 11863.1221719457
8178.7330316742 0.0) (11 12109.0214932127 8178.7330316742 0.0))
((0 . "LINE") (100 . "AcDbEntity") (8 . "SOLAR") (62 . 7) (370 . 13) (100 . "AcDbLine") (10 12109.0214932127
8178.7330316742 0.0) (11 12101.1354638009 8165.4977375566 0.0))
((0 . "LINE") (100 . "AcDbEntity") (8 . "SOLAR") (62 . 7) (370 . 13) (100 . "AcDbLine") (10 12101.1354638009
8165.4977375566 0.0) (11 12067.5187330317 8109.0780542986 0.0))
((0 . "LINE") (100 . "AcDbEntity") (8 . "SOLAR") (62 . 7) (370 . 13) (100 . "AcDbLine") (10 12067.5187330317
8109.0780542986 0.0) (11 12039.6648755656 8062.3303167421 0.0))
((0 . "LINE") (100 . "AcDbEntity") (8 . "SOLAR") (62 . 7) (370 . 13) (100 . "AcDbLine") (10 12039.6648755656
8062.3303167421 0.0) (11 12021.4157918552 8031.7024886878 0.0))
((0 . "LINE") (100 . "AcDbEntity") (8 . "SOLAR") (62 . 7) (370 . 13) (100 . "AcDbLine") (10 12021.4157918552
8031.7024886878 0.0) (11 12001.2457579186 7997.850678733 0.0))
((0 . "LINE") (100 . "AcDbEntity") (8 . "SOLAR") (62 . 7) (370 . 13) (100 . "AcDbLine") (10 12001.2457579186
7997.850678733 0.0) (11 11975.3128506787 7954.3269230769 0.0))
((0 . "LINE") (100 . "AcDbEntity") (8 . "SOLAR") (62 . 7) (370 . 13) (100 . "AcDbLine") (10 11975.3128506787
7954.3269230769 0.0) (11 11947.2567873303 7907.2398190045 0.0))
((0 . "LINE") (100 . "AcDbEntity") (8 . "SOLAR") (62 . 7) (370 . 13) (100 . "AcDbLine") (10 11947.2567873303
7907.2398190045 0.0) (11 11715.3091968326 7907.2398190045 0.0))
((0 . "LINE") (100 . "AcDbEntity") (8 . "SOLAR") (62 . 7) (370 . 13) (100 . "AcDbLine") (10 11715.3091968326
7907.2398190045 0.0) (11 11464.5550565611 7907.2398190045 0.0))
((0 . "LINE") (100 . "AcDbEntity") (8 . "SOLAR") (62 . 7) (370 . 13) (100 . "AcDbLine") (10 11464.5550565611
7907.2398190045 0.0) (11 11232.6074660633 7907.2398190045 0.0))
((0 . "LINE") (100 . "AcDbEntity") (8 . "SOLAR") (62 . 7) (370 . 13) (100 . "AcDbLine") (10 11232.6074660633
7907.2398190045 0.0) (11 11253.2080769231 7954.3269230769 0.0))
((0 . "LINE") (100 . "AcDbEntity") (8 . "SOLAR") (62 . 7) (370 . 13) (100 . "AcDbLine") (10 11253.2080769231
7954.3269230769 0.0) (11 11272.2497171946 7997.850678733 0.0))
((0 . "LINE") (100 . "AcDbEntity") (8 . "SOLAR") (62 . 7) (370 . 13) (100 . "AcDbLine") (10 11272.2497171946
7997.850678733 0.0) (11 11287.0598868778 8031.7024886878 0.0))
((0 . "LINE") (100 . "AcDbEntity") (8 . "SOLAR") (62 . 7) (370 . 13) (100 . "AcDbLine") (10 11287.0598868778
8031.7024886878 0.0) (11 11300.4595588235 8062.3303167421 0.0))
((0 . "LINE") (100 . "AcDbEntity") (8 . "SOLAR") (62 . 7) (370 . 13) (100 . "AcDbLine") (10 11300.4595588235
8062.3303167421 0.0) (11 11320.9116968326 8109.0780542986 0.0))
((0 . "LINE") (100 . "AcDbEntity") (8 . "SOLAR") (62 . 7) (370 . 13) (100 . "AcDbLine") (10 11320.9116968326
8109.0780542986 0.0) (11 11345.5953054299 8165.4977375566 0.0))
((0 . "LINE") (100 . "AcDbEntity") (8 . "SOLAR") (62 . 7) (370 . 13) (100 . "AcDbLine") (10 11345.5953054299
8165.4977375566 0.0) (11 11351.3857466063 8178.7330316742 0.0))
((0 . "LINE") (100 . "AcDbEntity") (8 . "SOLAR") (62 . 7) (370 . 13) (100 . "AcDbLine") (10 11597.2850678733
8178.7330316742 0.0) (11 11590.814479638 8165.4977375566 0.0))
((0 . "LINE") (100 . "AcDbEntity") (8 . "SOLAR") (62 . 7) (370 . 13) (100 . "AcDbLine") (10 11590.814479638
8165.4977375566 0.0) (11 11563.2315271493 8109.0780542986 0.0))
((0 . "LINE") (100 . "AcDbEntity") (8 . "SOLAR") (62 . 7) (370 . 13) (100 . "AcDbLine") (10 11563.2315271493
8109.0780542986 0.0) (11 11540.3770701357 8062.3303167421 0.0))
((0 . "LINE") (100 . "AcDbEntity") (8 . "SOLAR") (62 . 7) (370 . 13) (100 . "AcDbLine") (10 11540.3770701357
8062.3303167421 0.0) (11 11525.4034728507 8031.7024886878 0.0))
((0 . "LINE") (100 . "AcDbEntity") (8 . "SOLAR") (62 . 7) (370 . 13) (100 . "AcDbLine") (10 11525.4034728507
8031.7024886878 0.0) (11 11508.853699095 7997.850678733 0.0))
((0 . "LINE") (100 . "AcDbEntity") (8 . "SOLAR") (62 . 7) (370 . 13) (100 . "AcDbLine") (10 11508.853699095
7997.850678733 0.0) (11 11487.575418552 7954.3269230769 0.0))
((0 . "LINE") (100 . "AcDbEntity") (8 . "SOLAR") (62 . 7) (370 . 13) (100 . "AcDbLine") (10 11487.575418552
7954.3269230769 0.0) (11 11464.5550565611 7907.2398190045 0.0))
((0 . "LINE") (100 . "AcDbEntity") (8 . "SOLAR") (62 . 7) (370 . 13) (100 . "AcDbLine") (10 11863.1221719457
8178.7330316742 0.0) (11 11855.9162895928 8165.4977375566 0.0))
((0 . "LINE") (100 . "AcDbEntity") (8 . "SOLAR") (62 . 7) (370 . 13) (100 . "AcDbLine") (10 11855.9162895928
8165.4977375566 0.0) (11 11825.1989027149 8109.0780542986 0.0))
((0 . "LINE") (100 . "AcDbEntity") (8 . "SOLAR") (62 . 7) (370 . 13) (100 . "AcDbLine") (10 11825.1989027149
8109.0780542986 0.0) (11 11799.7473642534 8062.3303167421 0.0))
((0 . "LINE") (100 . "AcDbEntity") (8 . "SOLAR") (62 . 7) (370 . 13) (100 . "AcDbLine") (10 11799.7473642534
8062.3303167421 0.0) (11 11783.0722058824 8031.7024886878 0.0))
((0 . "LINE") (100 . "AcDbEntity") (8 . "SOLAR") (62 . 7) (370 . 13) (100 . "AcDbLine") (10 11783.0722058824
8031.7024886878 0.0) (11 11764.6417760181 7997.850678733 0.0))
((0 . "LINE") (100 . "AcDbEntity") (8 . "SOLAR") (62 . 7) (370 . 13) (100 . "AcDbLine") (10 11764.6417760181
7997.850678733 0.0) (11 11740.9455090498 7954.3269230769 0.0))
((0 . "LINE") (100 . "AcDbEntity") (8 . "SOLAR") (62 . 7) (370 . 13) (100 . "AcDbLine") (10 11740.9455090498
7954.3269230769 0.0) (11 11715.3091968326 7907.2398190045 0.0))
((0 . "LINE") (100 . "AcDbEntity") (8 . "SOLAR") (62 . 7) (370 . 13) (100 . "AcDbLine") (10 11345.5953054299
8165.4977375566 0.0) (11 11590.814479638 8165.4977375566 0.0))
((0 . "LINE") (100 . "AcDbEntity") (8 . "SOLAR") (62 . 7) (370 . 13) (100 . "AcDbLine") (10 11590.814479638
8165.4977375566 0.0) (11 11855.9162895928 8165.4977375566 0.0))
((0 . "LINE") (100 . "AcDbEntity") (8 . "SOLAR") (62 . 7) (370 . 13) (100 . "AcDbLine") (10 11855.9162895928
8165.4977375566 0.0) (11 12101.1354638009 8165.4977375566 0.0))
((0 . "LINE") (100 . "AcDbEntity") (8 . "SOLAR") (62 . 7) (370 . 13) (100 . "AcDbLine") (10 11320.9116968326
8109.0780542986 0.0) (11 11563.2315271493 8109.0780542986 0.0))
((0 . "LINE") (100 . "AcDbEntity") (8 . "SOLAR") (62 . 7) (370 . 13) (100 . "AcDbLine") (10 11563.2315271493
8109.0780542986 0.0) (11 11825.1989027149 8109.0780542986 0.0))
((0 . "LINE") (100 . "AcDbEntity") (8 . "SOLAR") (62 . 7) (370 . 13) (100 . "AcDbLine") (10 11825.1989027149
8109.0780542986 0.0) (11 12067.5187330317 8109.0780542986 0.0))
((0 . "LINE") (100 . "AcDbEntity") (8 . "SOLAR") (62 . 7) (370 . 13) (100 . "AcDbLine") (10 11300.4595588235
8062.3303167421 0.0) (11 11540.3770701357 8062.3303167421 0.0))
((0 . "LINE") (100 . "AcDbEntity") (8 . "SOLAR") (62 . 7) (370 . 13) (100 . "AcDbLine") (10 11540.3770701357
8062.3303167421 0.0) (11 11799.7473642534 8062.3303167421 0.0))
((0 . "LINE") (100 . "AcDbEntity") (8 . "SOLAR") (62 . 7) (370 . 13) (100 . "AcDbLine") (10 11799.7473642534
8062.3303167421 0.0) (11 12039.6648755656 8062.3303167421 0.0))
((0 . "LINE") (100 . "AcDbEntity") (8 . "SOLAR") (62 . 7) (370 . 13) (100 . "AcDbLine") (10 11287.0598868778
8031.7024886878 0.0) (11 11525.4034728507 8031.7024886878 0.0))
((0 . "LINE") (100 . "AcDbEntity") (8 . "SOLAR") (62 . 7) (370 . 13) (100 . "AcDbLine") (10 11525.4034728507
8031.7024886878 0.0) (11 11783.0722058824 8031.7024886878 0.0))
((0 . "LINE") (100 . "AcDbEntity") (8 . "SOLAR") (62 . 7) (370 . 13) (100 . "AcDbLine") (10 11783.0722058824
8031.7024886878 0.0) (11 12021.4157918552 8031.7024886878 0.0))
((0 . "LINE") (100 . "AcDbEntity") (8 . "SOLAR") (62 . 7) (370 . 13) (100 . "AcDbLine") (10 11272.2497171946
7997.850678733 0.0) (11 11508.853699095 7997.850678733 0.0))
((0 . "LINE") (100 . "AcDbEntity") (8 . "SOLAR") (62 . 7) (370 . 13) (100 . "AcDbLine") (10 11508.853699095
7997.850678733 0.0) (11 11764.6417760181 7997.850678733 0.0))
((0 . "LINE") (100 . "AcDbEntity") (8 . "SOLAR") (62 . 7) (370 . 13) (100 . "AcDbLine") (10 11764.6417760181
7997.850678733 0.0) (11 12001.2457579186 7997.850678733 0.0))
((0 . "LINE") (100 . "AcDbEntity") (8 . "SOLAR") (62 . 7) (370 . 13) (100 . "AcDbLine") (10 11253.2080769231
7954.3269230769 0.0) (11 11487.575418552 7954.3269230769 0.0))
((0 . "LINE") (100 . "AcDbEntity") (8 . "SOLAR") (62 . 7) (370 . 13) (100 . "AcDbLine") (10 11487.575418552
7954.3269230769 0.0) (11 11740.9455090498 7954.3269230769 0.0))
((0 . "LINE") (100 . "AcDbEntity") (8 . "SOLAR") (62 . 7) (370 . 13) (100 . "AcDbLine") (10 11740.9455090498
7954.3269230769 0.0) (11 11975.3128506787 7954.3269230769 0.0))
((0 . "LINE") (100 . "AcDbEntity") (8 . "SOLAR") (62 . 7) (370 . 13) (100 . "AcDbLine") (10 12522.6244343891
8212.6696832579 0.0) (11 13212.6696832579 8212.6696832579 0.0))
((0 . "LINE") (100 . "AcDbEntity") (8 . "SOLAR") (62 . 7) (370 . 13) (100 . "AcDbLine") (10 13212.6696832579
8212.6696832579 0.0) (11 12986.4253393665 7873.3031674208 0.0))
((0 . "LINE") (100 . "AcDbEntity") (8 . "SOLAR") (62 . 7) (370 . 13) (100 . "AcDbLine") (10 12986.4253393665
7873.3031674208 0.0) (11 12319.0045248869 7873.3031674208 0.0))
((0 . "LINE") (100 . "AcDbEntity") (8 . "SOLAR") (62 . 7) (370 . 13) (100 . "AcDbLine") (10 12319.0045248869
7873.3031674208 0.0) (11 12522.6244343891 8212.6696832579 0.0))
((0 . "LINE") (100 . "AcDbEntity") (8 . "SOLAR") (62 . 7) (370 . 13) (100 . "AcDbLine") (10 12519.4570135747
8178.7330316742 0.0) (11 12731.5233823529 8178.7330316742 0.0))
((0 . "LINE") (100 . "AcDbEntity") (8 . "SOLAR") (62 . 7) (370 . 13) (100 . "AcDbLine") (10 12731.5233823529
8178.7330316742 0.0) (11 12960.7843099547 8178.7330316742 0.0))
((0 . "LINE") (100 . "AcDbEntity") (8 . "SOLAR") (62 . 7) (370 . 13) (100 . "AcDbLine") (10 12960.7843099547
8178.7330316742 0.0) (11 13172.850678733 8178.7330316742 0.0))
((0 . "LINE") (100 . "AcDbEntity") (8 . "SOLAR") (62 . 7) (370 . 13) (100 . "AcDbLine") (10 13172.850678733
8178.7330316742 0.0) (11 13164.0492081448 8165.4977375566 0.0))
((0 . "LINE") (100 . "AcDbEntity") (8 . "SOLAR") (62 . 7) (370 . 13) (100 . "AcDbLine") (10 13164.0492081448
8165.4977375566 0.0) (11 13125.4581447964 8107.4660633484 0.0))
((0 . "LINE") (100 . "AcDbEntity") (8 . "SOLAR") (62 . 7) (370 . 13) (100 . "AcDbLine") (10 13125.4581447964
8107.4660633484 0.0) (11 13096.5148529412 8063.9423076923 0.0))
((0 . "LINE") (100 . "AcDbEntity") (8 . "SOLAR") (62 . 7) (370 . 13) (100 . "AcDbLine") (10 13096.5148529412
8063.9423076923 0.0) (11 13066.4995701357 8018.806561086 0.0))
((0 . "LINE") (100 . "AcDbEntity") (8 . "SOLAR") (62 . 7) (370 . 13) (100 . "AcDbLine") (10 13066.4995701357
8018.806561086 0.0) (11 13037.5562782805 7975.2828054299 0.0))
((0 . "LINE") (100 . "AcDbEntity") (8 . "SOLAR") (62 . 7) (370 . 13) (100 . "AcDbLine") (10 13037.5562782805
7975.2828054299 0.0) (11 13016.1167986425 7943.0429864253 0.0))
((0 . "LINE") (100 . "AcDbEntity") (8 . "SOLAR") (62 . 7) (370 . 13) (100 . "AcDbLine") (10 13016.1167986425
7943.0429864253 0.0) (11 12992.3076923077 7907.2398190045 0.0))
((0 . "LINE") (100 . "AcDbEntity") (8 . "SOLAR") (62 . 7) (370 . 13) (100 . "AcDbLine") (10 12992.3076923077
7907.2398190045 0.0) (11 12785.8220248869 7907.2398190045 0.0))
((0 . "LINE") (100 . "AcDbEntity") (8 . "SOLAR") (62 . 7) (370 . 13) (100 . "AcDbLine") (10 12785.8220248869
7907.2398190045 0.0) (11 12562.5942647059 7907.2398190045 0.0))
((0 . "LINE") (100 . "AcDbEntity") (8 . "SOLAR") (62 . 7) (370 . 13) (100 . "AcDbLine") (10 12562.5942647059
7907.2398190045 0.0) (11 12356.1085972851 7907.2398190045 0.0))
((0 . "LINE") (100 . "AcDbEntity") (8 . "SOLAR") (62 . 7) (370 . 13) (100 . "AcDbLine") (10 12356.1085972851
7907.2398190045 0.0) (11 12377.6501696833 7943.0429864253 0.0))
((0 . "LINE") (100 . "AcDbEntity") (8 . "SOLAR") (62 . 7) (370 . 13) (100 . "AcDbLine") (10 12377.6501696833
7943.0429864253 0.0) (11 12397.0477941176 7975.2828054299 0.0))
((0 . "LINE") (100 . "AcDbEntity") (8 . "SOLAR") (62 . 7) (370 . 13) (100 . "AcDbLine") (10 12397.0477941176
7975.2828054299 0.0) (11 12423.2345927602 8018.806561086 0.0))
((0 . "LINE") (100 . "AcDbEntity") (8 . "SOLAR") (62 . 7) (370 . 13) (100 . "AcDbLine") (10 12423.2345927602
8018.806561086 0.0) (11 12450.3912669683 8063.9423076923 0.0))
((0 . "LINE") (100 . "AcDbEntity") (8 . "SOLAR") (62 . 7) (370 . 13) (100 . "AcDbLine") (10 12450.3912669683
8063.9423076923 0.0) (11 12476.5780542986 8107.4660633484 0.0))
((0 . "LINE") (100 . "AcDbEntity") (8 . "SOLAR") (62 . 7) (370 . 13) (100 . "AcDbLine") (10 12476.5780542986
8107.4660633484 0.0) (11 12511.4937782805 8165.4977375566 0.0))
((0 . "LINE") (100 . "AcDbEntity") (8 . "SOLAR") (62 . 7) (370 . 13) (100 . "AcDbLine") (10 12511.4937782805
8165.4977375566 0.0) (11 12519.4570135747 8178.7330316742 0.0))
((0 . "LINE") (100 . "AcDbEntity") (8 . "SOLAR") (62 . 7) (370 . 13) (100 . "AcDbLine") (10 12731.5233823529
8178.7330316742 0.0) (11 12723.2880882353 8165.4977375566 0.0))
((0 . "LINE") (100 . "AcDbEntity") (8 . "SOLAR") (62 . 7) (370 . 13) (100 . "AcDbLine") (10 12723.2880882353
8165.4977375566 0.0) (11 12687.1794909502 8107.4660633484 0.0))
((0 . "LINE") (100 . "AcDbEntity") (8 . "SOLAR") (62 . 7) (370 . 13) (100 . "AcDbLine") (10 12687.1794909502
8107.4660633484 0.0) (11 12660.0980429864 8063.9423076923 0.0))
((0 . "LINE") (100 . "AcDbEntity") (8 . "SOLAR") (62 . 7) (370 . 13) (100 . "AcDbLine") (10 12660.0980429864
8063.9423076923 0.0) (11 12632.0135746606 8018.806561086 0.0))
((0 . "LINE") (100 . "AcDbEntity") (8 . "SOLAR") (62 . 7) (370 . 13) (100 . "AcDbLine") (10 12632.0135746606
8018.806561086 0.0) (11 12604.9321266968 7975.2828054299 0.0))
((0 . "LINE") (100 . "AcDbEntity") (8 . "SOLAR") (62 . 7) (370 . 13) (100 . "AcDbLine") (10 12604.9321266968
7975.2828054299 0.0) (11 12584.8717986425 7943.0429864253 0.0))
((0 . "LINE") (100 . "AcDbEntity") (8 . "SOLAR") (62 . 7) (370 . 13) (100 . "AcDbLine") (10 12584.8717986425
7943.0429864253 0.0) (11 12562.5942647059 7907.2398190045 0.0))
((0 . "LINE") (100 . "AcDbEntity") (8 . "SOLAR") (62 . 7) (370 . 13) (100 . "AcDbLine") (10 12960.7843099547
8178.7330316742 0.0) (11 12952.25489819 8165.4977375566 0.0))
((0 . "LINE") (100 . "AcDbEntity") (8 . "SOLAR") (62 . 7) (370 . 13) (100 . "AcDbLine") (10 12952.25489819
8165.4977375566 0.0) (11 12914.8567081448 8107.4660633484 0.0))
((0 . "LINE") (100 . "AcDbEntity") (8 . "SOLAR") (62 . 7) (370 . 13) (100 . "AcDbLine") (10 12914.8567081448
8107.4660633484 0.0) (11 12886.8080656109 8063.9423076923 0.0))
((0 . "LINE") (100 . "AcDbEntity") (8 . "SOLAR") (62 . 7) (370 . 13) (100 . "AcDbLine") (10 12886.8080656109
8063.9423076923 0.0) (11 12857.7205882353 8018.806561086 0.0))
((0 . "LINE") (100 . "AcDbEntity") (8 . "SOLAR") (62 . 7) (370 . 13) (100 . "AcDbLine") (10 12857.7205882353
8018.806561086 0.0) (11 12829.6719457014 7975.2828054299 0.0))
((0 . "LINE") (100 . "AcDbEntity") (8 . "SOLAR") (62 . 7) (370 . 13) (100 . "AcDbLine") (10 12829.6719457014
7975.2828054299 0.0) (11 12808.8951696833 7943.0429864253 0.0))
((0 . "LINE") (100 . "AcDbEntity") (8 . "SOLAR") (62 . 7) (370 . 13) (100 . "AcDbLine") (10 12808.8951696833
7943.0429864253 0.0) (11 12785.8220248869 7907.2398190045 0.0))
((0 . "LINE") (100 . "AcDbEntity") (8 . "SOLAR") (62 . 7) (370 . 13) (100 . "AcDbLine") (10 12511.4937782805
8165.4977375566 0.0) (11 12723.2880882353 8165.4977375566 0.0))
((0 . "LINE") (100 . "AcDbEntity") (8 . "SOLAR") (62 . 7) (370 . 13) (100 . "AcDbLine") (10 12723.2880882353
8165.4977375566 0.0) (11 12952.25489819 8165.4977375566 0.0))
((0 . "LINE") (100 . "AcDbEntity") (8 . "SOLAR") (62 . 7) (370 . 13) (100 . "AcDbLine") (10 12952.25489819
8165.4977375566 0.0) (11 13164.0492081448 8165.4977375566 0.0))
((0 . "LINE") (100 . "AcDbEntity") (8 . "SOLAR") (62 . 7) (370 . 13) (100 . "AcDbLine") (10 12476.5780542986
8107.4660633484 0.0) (11 12687.1794909502 8107.4660633484 0.0))
((0 . "LINE") (100 . "AcDbEntity") (8 . "SOLAR") (62 . 7) (370 . 13) (100 . "AcDbLine") (10 12687.1794909502
8107.4660633484 0.0) (11 12914.8567081448 8107.4660633484 0.0))
((0 . "LINE") (100 . "AcDbEntity") (8 . "SOLAR") (62 . 7) (370 . 13) (100 . "AcDbLine") (10 12914.8567081448
8107.4660633484 0.0) (11 13125.4581447964 8107.4660633484 0.0))
((0 . "LINE") (100 . "AcDbEntity") (8 . "SOLAR") (62 . 7) (370 . 13) (100 . "AcDbLine") (10 12450.3912669683
8063.9423076923 0.0) (11 12660.0980429864 8063.9423076923 0.0))
((0 . "LINE") (100 . "AcDbEntity") (8 . "SOLAR") (62 . 7) (370 . 13) (100 . "AcDbLine") (10 12660.0980429864
8063.9423076923 0.0) (11 12886.8080656109 8063.9423076923 0.0))
((0 . "LINE") (100 . "AcDbEntity") (8 . "SOLAR") (62 . 7) (370 . 13) (100 . "AcDbLine") (10 12886.8080656109
8063.9423076923 0.0) (11 13096.5148529412 8063.9423076923 0.0))
((0 . "LINE") (100 . "AcDbEntity") (8 . "SOLAR") (62 . 7) (370 . 13) (100 . "AcDbLine") (10 12423.2345927602
8018.806561086 0.0) (11 12632.0135746606 8018.806561086 0.0))
((0 . "LINE") (100 . "AcDbEntity") (8 . "SOLAR") (62 . 7) (370 . 13) (100 . "AcDbLine") (10 12632.0135746606
8018.806561086 0.0) (11 12857.7205882353 8018.806561086 0.0))
((0 . "LINE") (100 . "AcDbEntity") (8 . "SOLAR") (62 . 7) (370 . 13) (100 . "AcDbLine") (10 12857.7205882353
8018.806561086 0.0) (11 13066.4995701357 8018.806561086 0.0))
((0 . "LINE") (100 . "AcDbEntity") (8 . "SOLAR") (62 . 7) (370 . 13) (100 . "AcDbLine") (10 12397.0477941176
7975.2828054299 0.0) (11 12604.9321266968 7975.2828054299 0.0))
((0 . "LINE") (100 . "AcDbEntity") (8 . "SOLAR") (62 . 7) (370 . 13) (100 . "AcDbLine") (10 12604.9321266968
7975.2828054299 0.0) (11 12829.6719457014 7975.2828054299 0.0))
((0 . "LINE") (100 . "AcDbEntity") (8 . "SOLAR") (62 . 7) (370 . 13) (100 . "AcDbLine") (10 12829.6719457014
7975.2828054299 0.0) (11 13037.5562782805 7975.2828054299 0.0))
((0 . "LINE") (100 . "AcDbEntity") (8 . "SOLAR") (62 . 7) (370 . 13) (100 . "AcDbLine") (10 12377.6501696833
7943.0429864253 0.0) (11 12584.8717986425 7943.0429864253 0.0))
((0 . "LINE") (100 . "AcDbEntity") (8 . "SOLAR") (62 . 7) (370 . 13) (100 . "AcDbLine") (10 12584.8717986425
7943.0429864253 0.0) (11 12808.8951696833 7943.0429864253 0.0))
((0 . "LINE") (100 . "AcDbEntity") (8 . "SOLAR") (62 . 7) (370 . 13) (100 . "AcDbLine") (10 12808.8951696833
7943.0429864253 0.0) (11 13016.1167986425 7943.0429864253 0.0))
((0 . "LINE") (100 . "AcDbEntity") (8 . "SOLAR") (62 . 7) (370 . 13) (100 . "AcDbLine") (10 13257.9185520362
8212.6696832579 0.0) (11 14027.149321267 8212.6696832579 0.0))
((0 . "LINE") (100 . "AcDbEntity") (8 . "SOLAR") (62 . 7) (370 . 13) (100 . "AcDbLine") (10 14027.149321267
8212.6696832579 0.0) (11 13823.5294117647 7873.3031674208 0.0))
((0 . "LINE") (100 . "AcDbEntity") (8 . "SOLAR") (62 . 7) (370 . 13) (100 . "AcDbLine") (10 13823.5294117647
7873.3031674208 0.0) (11 13031.6742081448 7873.3031674208 0.0))
((0 . "LINE") (100 . "AcDbEntity") (8 . "SOLAR") (62 . 7) (370 . 13) (100 . "AcDbLine") (10 13031.6742081448
7873.3031674208 0.0) (11 13257.9185520362 8212.6696832579 0.0))
((0 . "LINE") (100 . "AcDbEntity") (8 . "SOLAR") (62 . 7) (370 . 13) (100 . "AcDbLine") (10 13254.5814479638
8178.7330316742 0.0) (11 13492.4585180995 8178.7330316742 0.0))
((0 . "LINE") (100 . "AcDbEntity") (8 . "SOLAR") (62 . 7) (370 . 13) (100 . "AcDbLine") (10 13492.4585180995
8178.7330316742 0.0) (11 13749.6229298643 8178.7330316742 0.0))
((0 . "LINE") (100 . "AcDbEntity") (8 . "SOLAR") (62 . 7) (370 . 13) (100 . "AcDbLine") (10 13749.6229298643
8178.7330316742 0.0) (11 13987.5 8178.7330316742 0.0))
((0 . "LINE") (100 . "AcDbEntity") (8 . "SOLAR") (62 . 7) (370 . 13) (100 . "AcDbLine") (10 13987.5 8178.7330316742 0.0)
(11 13979.5367647059 8165.4977375566 0.0))
((0 . "LINE") (100 . "AcDbEntity") (8 . "SOLAR") (62 . 7) (370 . 13) (100 . "AcDbLine") (10 13979.5367647059
8165.4977375566 0.0) (11 13944.621040724 8107.4660633484 0.0))
((0 . "LINE") (100 . "AcDbEntity") (8 . "SOLAR") (62 . 7) (370 . 13) (100 . "AcDbLine") (10 13944.621040724
8107.4660633484 0.0) (11 13917.4643665158 8062.3303167421 0.0))
((0 . "LINE") (100 . "AcDbEntity") (8 . "SOLAR") (62 . 7) (370 . 13) (100 . "AcDbLine") (10 13917.4643665158
8062.3303167421 0.0) (11 13886.4281674208 8010.7466063348 0.0))
((0 . "LINE") (100 . "AcDbEntity") (8 . "SOLAR") (62 . 7) (370 . 13) (100 . "AcDbLine") (10 13886.4281674208
8010.7466063348 0.0) (11 13865.090780543 7975.2828054299 0.0))
((0 . "LINE") (100 . "AcDbEntity") (8 . "SOLAR") (62 . 7) (370 . 13) (100 . "AcDbLine") (10 13865.090780543
7975.2828054299 0.0) (11 13844.723280543 7941.4309954751 0.0))
((0 . "LINE") (100 . "AcDbEntity") (8 . "SOLAR") (62 . 7) (370 . 13) (100 . "AcDbLine") (10 13844.723280543
7941.4309954751 0.0) (11 13824.1515837104 7907.2398190045 0.0))
((0 . "LINE") (100 . "AcDbEntity") (8 . "SOLAR") (62 . 7) (370 . 13) (100 . "AcDbLine") (10 13824.1515837104
7907.2398190045 0.0) (11 13580.6938122172 7907.2398190045 0.0))
((0 . "LINE") (100 . "AcDbEntity") (8 . "SOLAR") (62 . 7) (370 . 13) (100 . "AcDbLine") (10 13580.6938122172
7907.2398190045 0.0) (11 13317.4962330317 7907.2398190045 0.0))
((0 . "LINE") (100 . "AcDbEntity") (8 . "SOLAR") (62 . 7) (370 . 13) (100 . "AcDbLine") (10 13317.4962330317
7907.2398190045 0.0) (11 13074.0384615385 7907.2398190045 0.0))
((0 . "LINE") (100 . "AcDbEntity") (8 . "SOLAR") (62 . 7) (370 . 13) (100 . "AcDbLine") (10 13074.0384615385
7907.2398190045 0.0) (11 13096.7755995475 7941.4309954751 0.0))
((0 . "LINE") (100 . "AcDbEntity") (8 . "SOLAR") (62 . 7) (370 . 13) (100 . "AcDbLine") (10 13096.7755995475
7941.4309954751 0.0) (11 13119.2870475113 7975.2828054299 0.0))
((0 . "LINE") (100 . "AcDbEntity") (8 . "SOLAR") (62 . 7) (370 . 13) (100 . "AcDbLine") (10 13119.2870475113
7975.2828054299 0.0) (11 13142.8704751131 8010.7466063348 0.0))
((0 . "LINE") (100 . "AcDbEntity") (8 . "SOLAR") (62 . 7) (370 . 13) (100 . "AcDbLine") (10 13142.8704751131
8010.7466063348 0.0) (11 13177.1736425339 8062.3303167421 0.0))
((0 . "LINE") (100 . "AcDbEntity") (8 . "SOLAR") (62 . 7) (370 . 13) (100 . "AcDbLine") (10 13177.1736425339
8062.3303167421 0.0) (11 13207.1889140272 8107.4660633484 0.0))
((0 . "LINE") (100 . "AcDbEntity") (8 . "SOLAR") (62 . 7) (370 . 13) (100 . "AcDbLine") (10 13207.1889140272
8107.4660633484 0.0) (11 13245.7799773756 8165.4977375566 0.0))
((0 . "LINE") (100 . "AcDbEntity") (8 . "SOLAR") (62 . 7) (370 . 13) (100 . "AcDbLine") (10 13245.7799773756
8165.4977375566 0.0) (11 13254.5814479638 8178.7330316742 0.0))
((0 . "LINE") (100 . "AcDbEntity") (8 . "SOLAR") (62 . 7) (370 . 13) (100 . "AcDbLine") (10 13492.4585180995
8178.7330316742 0.0) (11 13483.9291063348 8165.4977375566 0.0))
((0 . "LINE") (100 . "AcDbEntity") (8 . "SOLAR") (62 . 7) (370 . 13) (100 . "AcDbLine") (10 13483.9291063348
8165.4977375566 0.0) (11 13446.5309162896 8107.4660633484 0.0))
((0 . "LINE") (100 . "AcDbEntity") (8 . "SOLAR") (62 . 7) (370 . 13) (100 . "AcDbLine") (10 13446.5309162896
8107.4660633484 0.0) (11 13417.443438914 8062.3303167421 0.0))
((0 . "LINE") (100 . "AcDbEntity") (8 . "SOLAR") (62 . 7) (370 . 13) (100 . "AcDbLine") (10 13417.443438914
8062.3303167421 0.0) (11 13384.2005995475 8010.7466063348 0.0))
((0 . "LINE") (100 . "AcDbEntity") (8 . "SOLAR") (62 . 7) (370 . 13) (100 . "AcDbLine") (10 13384.2005995475
8010.7466063348 0.0) (11 13361.3461538462 7975.2828054299 0.0))
((0 . "LINE") (100 . "AcDbEntity") (8 . "SOLAR") (62 . 7) (370 . 13) (100 . "AcDbLine") (10 13361.3461538462
7975.2828054299 0.0) (11 13339.5305429864 7941.4309954751 0.0))
((0 . "LINE") (100 . "AcDbEntity") (8 . "SOLAR") (62 . 7) (370 . 13) (100 . "AcDbLine") (10 13339.5305429864
7941.4309954751 0.0) (11 13317.4962330317 7907.2398190045 0.0))
((0 . "LINE") (100 . "AcDbEntity") (8 . "SOLAR") (62 . 7) (370 . 13) (100 . "AcDbLine") (10 13749.6229298643
8178.7330316742 0.0) (11 13741.3876357466 8165.4977375566 0.0))
((0 . "LINE") (100 . "AcDbEntity") (8 . "SOLAR") (62 . 7) (370 . 13) (100 . "AcDbLine") (10 13741.3876357466
8165.4977375566 0.0) (11 13705.2790384615 8107.4660633484 0.0))
((0 . "LINE") (100 . "AcDbEntity") (8 . "SOLAR") (62 . 7) (370 . 13) (100 . "AcDbLine") (10 13705.2790384615
8107.4660633484 0.0) (11 13677.1945701357 8062.3303167421 0.0))
((0 . "LINE") (100 . "AcDbEntity") (8 . "SOLAR") (62 . 7) (370 . 13) (100 . "AcDbLine") (10 13677.1945701357
8062.3303167421 0.0) (11 13645.0980429864 8010.7466063348 0.0))
((0 . "LINE") (100 . "AcDbEntity") (8 . "SOLAR") (62 . 7) (370 . 13) (100 . "AcDbLine") (10 13645.0980429864
8010.7466063348 0.0) (11 13623.0316742081 7975.2828054299 0.0))
((0 . "LINE") (100 . "AcDbEntity") (8 . "SOLAR") (62 . 7) (370 . 13) (100 . "AcDbLine") (10 13623.0316742081
7975.2828054299 0.0) (11 13601.9683257919 7941.4309954751 0.0))
((0 . "LINE") (100 . "AcDbEntity") (8 . "SOLAR") (62 . 7) (370 . 13) (100 . "AcDbLine") (10 13601.9683257919
7941.4309954751 0.0) (11 13580.6938122172 7907.2398190045 0.0))
((0 . "LINE") (100 . "AcDbEntity") (8 . "SOLAR") (62 . 7) (370 . 13) (100 . "AcDbLine") (10 13245.7799773756
8165.4977375566 0.0) (11 13483.9291063348 8165.4977375566 0.0))
((0 . "LINE") (100 . "AcDbEntity") (8 . "SOLAR") (62 . 7) (370 . 13) (100 . "AcDbLine") (10 13483.9291063348
8165.4977375566 0.0) (11 13741.3876357466 8165.4977375566 0.0))
((0 . "LINE") (100 . "AcDbEntity") (8 . "SOLAR") (62 . 7) (370 . 13) (100 . "AcDbLine") (10 13741.3876357466
8165.4977375566 0.0) (11 13979.5367647059 8165.4977375566 0.0))
((0 . "LINE") (100 . "AcDbEntity") (8 . "SOLAR") (62 . 7) (370 . 13) (100 . "AcDbLine") (10 13207.1889140272
8107.4660633484 0.0) (11 13446.5309162896 8107.4660633484 0.0))
((0 . "LINE") (100 . "AcDbEntity") (8 . "SOLAR") (62 . 7) (370 . 13) (100 . "AcDbLine") (10 13446.5309162896
8107.4660633484 0.0) (11 13705.2790384615 8107.4660633484 0.0))
((0 . "LINE") (100 . "AcDbEntity") (8 . "SOLAR") (62 . 7) (370 . 13) (100 . "AcDbLine") (10 13705.2790384615
8107.4660633484 0.0) (11 13944.621040724 8107.4660633484 0.0))
((0 . "LINE") (100 . "AcDbEntity") (8 . "SOLAR") (62 . 7) (370 . 13) (100 . "AcDbLine") (10 13177.1736425339
8062.3303167421 0.0) (11 13417.443438914 8062.3303167421 0.0))
((0 . "LINE") (100 . "AcDbEntity") (8 . "SOLAR") (62 . 7) (370 . 13) (100 . "AcDbLine") (10 13417.443438914
8062.3303167421 0.0) (11 13677.1945701357 8062.3303167421 0.0))
((0 . "LINE") (100 . "AcDbEntity") (8 . "SOLAR") (62 . 7) (370 . 13) (100 . "AcDbLine") (10 13677.1945701357
8062.3303167421 0.0) (11 13917.4643665158 8062.3303167421 0.0))
((0 . "LINE") (100 . "AcDbEntity") (8 . "SOLAR") (62 . 7) (370 . 13) (100 . "AcDbLine") (10 13142.8704751131
8010.7466063348 0.0) (11 13384.2005995475 8010.7466063348 0.0))
((0 . "LINE") (100 . "AcDbEntity") (8 . "SOLAR") (62 . 7) (370 . 13) (100 . "AcDbLine") (10 13384.2005995475
8010.7466063348 0.0) (11 13645.0980429864 8010.7466063348 0.0))
((0 . "LINE") (100 . "AcDbEntity") (8 . "SOLAR") (62 . 7) (370 . 13) (100 . "AcDbLine") (10 13645.0980429864
8010.7466063348 0.0) (11 13886.4281674208 8010.7466063348 0.0))
((0 . "LINE") (100 . "AcDbEntity") (8 . "SOLAR") (62 . 7) (370 . 13) (100 . "AcDbLine") (10 13119.2870475113
7975.2828054299 0.0) (11 13361.3461538462 7975.2828054299 0.0))
((0 . "LINE") (100 . "AcDbEntity") (8 . "SOLAR") (62 . 7) (370 . 13) (100 . "AcDbLine") (10 13361.3461538462
7975.2828054299 0.0) (11 13623.0316742081 7975.2828054299 0.0))
((0 . "LINE") (100 . "AcDbEntity") (8 . "SOLAR") (62 . 7) (370 . 13) (100 . "AcDbLine") (10 13623.0316742081
7975.2828054299 0.0) (11 13865.090780543 7975.2828054299 0.0))
((0 . "LINE") (100 . "AcDbEntity") (8 . "SOLAR") (62 . 7) (370 . 13) (100 . "AcDbLine") (10 13096.7755995475
7941.4309954751 0.0) (11 13339.5305429864 7941.4309954751 0.0))
((0 . "LINE") (100 . "AcDbEntity") (8 . "SOLAR") (62 . 7) (370 . 13) (100 . "AcDbLine") (10 13339.5305429864
7941.4309954751 0.0) (11 13601.9683257919 7941.4309954751 0.0))
((0 . "LINE") (100 . "AcDbEntity") (8 . "SOLAR") (62 . 7) (370 . 13) (100 . "AcDbLine") (10 13601.9683257919
7941.4309954751 0.0) (11 13844.723280543 7941.4309954751 0.0))
((0 . "LINE") (100 . "AcDbEntity") (8 . "SOLAR") (62 . 7) (370 . 13) (100 . "AcDbLine") (10 14072.3981900452
8212.6696832579 0.0) (11 14966.0633484163 8212.6696832579 0.0))
((0 . "LINE") (100 . "AcDbEntity") (8 . "SOLAR") (62 . 7) (370 . 13) (100 . "AcDbLine") (10 14966.0633484163
8212.6696832579 0.0) (11 14751.1312217195 7873.3031674208 0.0))
((0 . "LINE") (100 . "AcDbEntity") (8 . "SOLAR") (62 . 7) (370 . 13) (100 . "AcDbLine") (10 14751.1312217195
7873.3031674208 0.0) (11 13868.778280543 7873.3031674208 0.0))
((0 . "LINE") (100 . "AcDbEntity") (8 . "SOLAR") (62 . 7) (370 . 13) (100 . "AcDbLine") (10 13868.778280543
7873.3031674208 0.0) (11 14072.3981900452 8212.6696832579 0.0))
((0 . "LINE") (100 . "AcDbEntity") (8 . "SOLAR") (62 . 7) (370 . 13) (100 . "AcDbLine") (10 14074.3495475113
8178.7330316742 0.0) (11 14349.5475113122 8178.7330316742 0.0))
((0 . "LINE") (100 . "AcDbEntity") (8 . "SOLAR") (62 . 7) (370 . 13) (100 . "AcDbLine") (10 14349.5475113122
8178.7330316742 0.0) (11 14647.0588235294 8178.7330316742 0.0))
((0 . "LINE") (100 . "AcDbEntity") (8 . "SOLAR") (62 . 7) (370 . 13) (100 . "AcDbLine") (10 14647.0588235294
8178.7330316742 0.0) (11 14922.2567873303 8178.7330316742 0.0))
((0 . "LINE") (100 . "AcDbEntity") (8 . "SOLAR") (62 . 7) (370 . 13) (100 . "AcDbLine") (10 14922.2567873303
8178.7330316742 0.0) (11 14913.8854638009 8165.4977375566 0.0))
((0 . "LINE") (100 . "AcDbEntity") (8 . "SOLAR") (62 . 7) (370 . 13) (100 . "AcDbLine") (10 14913.8854638009
8165.4977375566 0.0) (11 14874.1216742081 8102.6300904977 0.0))
((0 . "LINE") (100 . "AcDbEntity") (8 . "SOLAR") (62 . 7) (370 . 13) (100 . "AcDbLine") (10 14874.1216742081
8102.6300904977 0.0) (11 14849.6516515837 8063.9423076923 0.0))
((0 . "LINE") (100 . "AcDbEntity") (8 . "SOLAR") (62 . 7) (370 . 13) (100 . "AcDbLine") (10 14849.6516515837
8063.9423076923 0.0) (11 14816.0053733032 8010.7466063348 0.0))
((0 . "LINE") (100 . "AcDbEntity") (8 . "SOLAR") (62 . 7) (370 . 13) (100 . "AcDbLine") (10 14816.0053733032
8010.7466063348 0.0) (11 14793.5745135747 7975.2828054299 0.0))
((0 . "LINE") (100 . "AcDbEntity") (8 . "SOLAR") (62 . 7) (370 . 13) (100 . "AcDbLine") (10 14793.5745135747
7975.2828054299 0.0) (11 14772.1632466063 7941.4309954751 0.0))
((0 . "LINE") (100 . "AcDbEntity") (8 . "SOLAR") (62 . 7) (370 . 13) (100 . "AcDbLine") (10 14772.1632466063
7941.4309954751 0.0) (11 14750.5373303167 7907.2398190045 0.0))
((0 . "LINE") (100 . "AcDbEntity") (8 . "SOLAR") (62 . 7) (370 . 13) (100 . "AcDbLine") (10 14750.5373303167
7907.2398190045 0.0) (11 14478.1297171946 7907.2398190045 0.0))
((0 . "LINE") (100 . "AcDbEntity") (8 . "SOLAR") (62 . 7) (370 . 13) (100 . "AcDbLine") (10 14478.1297171946
7907.2398190045 0.0) (11 14183.6349886878 7907.2398190045 0.0))
((0 . "LINE") (100 . "AcDbEntity") (8 . "SOLAR") (62 . 7) (370 . 13) (100 . "AcDbLine") (10 14183.6349886878
7907.2398190045 0.0) (11 13911.2273755656 7907.2398190045 0.0))
((0 . "LINE") (100 . "AcDbEntity") (8 . "SOLAR") (62 . 7) (370 . 13) (100 . "AcDbLine") (10 13911.2273755656
7907.2398190045 0.0) (11 13931.7705769231 7941.4309954751 0.0))
((0 . "LINE") (100 . "AcDbEntity") (8 . "SOLAR") (62 . 7) (370 . 13) (100 . "AcDbLine") (10 13931.7705769231
7941.4309954751 0.0) (11 13952.1098755656 7975.2828054299 0.0))
((0 . "LINE") (100 . "AcDbEntity") (8 . "SOLAR") (62 . 7) (370 . 13) (100 . "AcDbLine") (10 13952.1098755656
7975.2828054299 0.0) (11 13973.4177036199 8010.7466063348 0.0))
((0 . "LINE") (100 . "AcDbEntity") (8 . "SOLAR") (62 . 7) (370 . 13) (100 . "AcDbLine") (10 13973.4177036199
8010.7466063348 0.0) (11 14005.3794570136 8063.9423076923 0.0))
((0 . "LINE") (100 . "AcDbEntity") (8 . "SOLAR") (62 . 7) (370 . 13) (100 . "AcDbLine") (10 14005.3794570136
8063.9423076923 0.0) (11 14028.6243665158 8102.6300904977 0.0))
((0 . "LINE") (100 . "AcDbEntity") (8 . "SOLAR") (62 . 7) (370 . 13) (100 . "AcDbLine") (10 14028.6243665158
8102.6300904977 0.0) (11 14066.397341629 8165.4977375566 0.0))
((0 . "LINE") (100 . "AcDbEntity") (8 . "SOLAR") (62 . 7) (370 . 13) (100 . "AcDbLine") (10 14066.397341629
8165.4977375566 0.0) (11 14074.3495475113 8178.7330316742 0.0))
((0 . "LINE") (100 . "AcDbEntity") (8 . "SOLAR") (62 . 7) (370 . 13) (100 . "AcDbLine") (10 14349.5475113122
8178.7330316742 0.0) (11 14341.4592760181 8165.4977375566 0.0))
((0 . "LINE") (100 . "AcDbEntity") (8 . "SOLAR") (62 . 7) (370 . 13) (100 . "AcDbLine") (10 14341.4592760181
8165.4977375566 0.0) (11 14303.040158371 8102.6300904977 0.0))
((0 . "LINE") (100 . "AcDbEntity") (8 . "SOLAR") (62 . 7) (370 . 13) (100 . "AcDbLine") (10 14303.040158371
8102.6300904977 0.0) (11 14279.3976244344 8063.9423076923 0.0))
((0 . "LINE") (100 . "AcDbEntity") (8 . "SOLAR") (62 . 7) (370 . 13) (100 . "AcDbLine") (10 14279.3976244344
8063.9423076923 0.0) (11 14246.8891402715 8010.7466063348 0.0))
((0 . "LINE") (100 . "AcDbEntity") (8 . "SOLAR") (62 . 7) (370 . 13) (100 . "AcDbLine") (10 14246.8891402715
8010.7466063348 0.0) (11 14225.216821267 7975.2828054299 0.0))
((0 . "LINE") (100 . "AcDbEntity") (8 . "SOLAR") (62 . 7) (370 . 13) (100 . "AcDbLine") (10 14225.216821267
7975.2828054299 0.0) (11 14204.5296040724 7941.4309954751 0.0))
((0 . "LINE") (100 . "AcDbEntity") (8 . "SOLAR") (62 . 7) (370 . 13) (100 . "AcDbLine") (10 14204.5296040724
7941.4309954751 0.0) (11 14183.6349886878 7907.2398190045 0.0))
((0 . "LINE") (100 . "AcDbEntity") (8 . "SOLAR") (62 . 7) (370 . 13) (100 . "AcDbLine") (10 14647.0588235294
8178.7330316742 0.0) (11 14638.8235294118 8165.4977375566 0.0))
((0 . "LINE") (100 . "AcDbEntity") (8 . "SOLAR") (62 . 7) (370 . 13) (100 . "AcDbLine") (10 14638.8235294118
8165.4977375566 0.0) (11 14599.7058823529 8102.6300904977 0.0))
((0 . "LINE") (100 . "AcDbEntity") (8 . "SOLAR") (62 . 7) (370 . 13) (100 . "AcDbLine") (10 14599.7058823529
8102.6300904977 0.0) (11 14575.6334841629 8063.9423076923 0.0))
((0 . "LINE") (100 . "AcDbEntity") (8 . "SOLAR") (62 . 7) (370 . 13) (100 . "AcDbLine") (10 14575.6334841629
8063.9423076923 0.0) (11 14542.5339366516 8010.7466063348 0.0))
((0 . "LINE") (100 . "AcDbEntity") (8 . "SOLAR") (62 . 7) (370 . 13) (100 . "AcDbLine") (10 14542.5339366516
8010.7466063348 0.0) (11 14520.4675678733 7975.2828054299 0.0))
((0 . "LINE") (100 . "AcDbEntity") (8 . "SOLAR") (62 . 7) (370 . 13) (100 . "AcDbLine") (10 14520.4675678733
7975.2828054299 0.0) (11 14499.404219457 7941.4309954751 0.0))
((0 . "LINE") (100 . "AcDbEntity") (8 . "SOLAR") (62 . 7) (370 . 13) (100 . "AcDbLine") (10 14499.404219457
7941.4309954751 0.0) (11 14478.1297171946 7907.2398190045 0.0))
((0 . "LINE") (100 . "AcDbEntity") (8 . "SOLAR") (62 . 7) (370 . 13) (100 . "AcDbLine") (10 14066.397341629
8165.4977375566 0.0) (11 14341.4592760181 8165.4977375566 0.0))
((0 . "LINE") (100 . "AcDbEntity") (8 . "SOLAR") (62 . 7) (370 . 13) (100 . "AcDbLine") (10 14341.4592760181
8165.4977375566 0.0) (11 14638.8235294118 8165.4977375566 0.0))
((0 . "LINE") (100 . "AcDbEntity") (8 . "SOLAR") (62 . 7) (370 . 13) (100 . "AcDbLine") (10 14638.8235294118
8165.4977375566 0.0) (11 14913.8854638009 8165.4977375566 0.0))
((0 . "LINE") (100 . "AcDbEntity") (8 . "SOLAR") (62 . 7) (370 . 13) (100 . "AcDbLine") (10 14028.6243665158
8102.6300904977 0.0) (11 14303.040158371 8102.6300904977 0.0))
((0 . "LINE") (100 . "AcDbEntity") (8 . "SOLAR") (62 . 7) (370 . 13) (100 . "AcDbLine") (10 14303.040158371
8102.6300904977 0.0) (11 14599.7058823529 8102.6300904977 0.0))
((0 . "LINE") (100 . "AcDbEntity") (8 . "SOLAR") (62 . 7) (370 . 13) (100 . "AcDbLine") (10 14599.7058823529
8102.6300904977 0.0) (11 14874.1216742081 8102.6300904977 0.0))
((0 . "LINE") (100 . "AcDbEntity") (8 . "SOLAR") (62 . 7) (370 . 13) (100 . "AcDbLine") (10 14005.3794570136
8063.9423076923 0.0) (11 14279.3976244344 8063.9423076923 0.0))
((0 . "LINE") (100 . "AcDbEntity") (8 . "SOLAR") (62 . 7) (370 . 13) (100 . "AcDbLine") (10 14279.3976244344
8063.9423076923 0.0) (11 14575.6334841629 8063.9423076923 0.0))
((0 . "LINE") (100 . "AcDbEntity") (8 . "SOLAR") (62 . 7) (370 . 13) (100 . "AcDbLine") (10 14575.6334841629
8063.9423076923 0.0) (11 14849.6516515837 8063.9423076923 0.0))
((0 . "LINE") (100 . "AcDbEntity") (8 . "SOLAR") (62 . 7) (370 . 13) (100 . "AcDbLine") (10 13973.4177036199
8010.7466063348 0.0) (11 14246.8891402715 8010.7466063348 0.0))
((0 . "LINE") (100 . "AcDbEntity") (8 . "SOLAR") (62 . 7) (370 . 13) (100 . "AcDbLine") (10 14246.8891402715
8010.7466063348 0.0) (11 14542.5339366516 8010.7466063348 0.0))
((0 . "LINE") (100 . "AcDbEntity") (8 . "SOLAR") (62 . 7) (370 . 13) (100 . "AcDbLine") (10 14542.5339366516
8010.7466063348 0.0) (11 14816.0053733032 8010.7466063348 0.0))
((0 . "LINE") (100 . "AcDbEntity") (8 . "SOLAR") (62 . 7) (370 . 13) (100 . "AcDbLine") (10 13952.1098755656
7975.2828054299 0.0) (11 14225.216821267 7975.2828054299 0.0))
((0 . "LINE") (100 . "AcDbEntity") (8 . "SOLAR") (62 . 7) (370 . 13) (100 . "AcDbLine") (10 14225.216821267
7975.2828054299 0.0) (11 14520.4675678733 7975.2828054299 0.0))
((0 . "LINE") (100 . "AcDbEntity") (8 . "SOLAR") (62 . 7) (370 . 13) (100 . "AcDbLine") (10 14520.4675678733
7975.2828054299 0.0) (11 14793.5745135747 7975.2828054299 0.0))
((0 . "LINE") (100 . "AcDbEntity") (8 . "SOLAR") (62 . 7) (370 . 13) (100 . "AcDbLine") (10 13931.7705769231
7941.4309954751 0.0) (11 14204.5296040724 7941.4309954751 0.0))
((0 . "LINE") (100 . "AcDbEntity") (8 . "SOLAR") (62 . 7) (370 . 13) (100 . "AcDbLine") (10 14204.5296040724
7941.4309954751 0.0) (11 14499.404219457 7941.4309954751 0.0))
((0 . "LINE") (100 . "AcDbEntity") (8 . "SOLAR") (62 . 7) (370 . 13) (100 . "AcDbLine") (10 14499.404219457
7941.4309954751 0.0) (11 14772.1632466063 7941.4309954751 0.0))
((0 . "LINE") (100 . "AcDbEntity") (8 . "SOLAR") (62 . 7) (370 . 13) (100 . "AcDbLine") (10 15011.3122171946
8212.6696832579 0.0) (11 15848.4162895928 8212.6696832579 0.0))
((0 . "LINE") (100 . "AcDbEntity") (8 . "SOLAR") (62 . 7) (370 . 13) (100 . "AcDbLine") (10 15848.4162895928
8212.6696832579 0.0) (11 15633.4841628959 7873.3031674208 0.0))
((0 . "LINE") (100 . "AcDbEntity") (8 . "SOLAR") (62 . 7) (370 . 13) (100 . "AcDbLine") (10 15633.4841628959
7873.3031674208 0.0) (11 14796.3800904977 7873.3031674208 0.0))
((0 . "LINE") (100 . "AcDbEntity") (8 . "SOLAR") (62 . 7) (370 . 13) (100 . "AcDbLine") (10 14796.3800904977
7873.3031674208 0.0) (11 15011.3122171946 8212.6696832579 0.0))
((0 . "LINE") (100 . "AcDbEntity") (8 . "SOLAR") (62 . 7) (370 . 13) (100 . "AcDbLine") (10 15010.7466063348
8178.7330316742 0.0) (11 15268.853699095 8178.7330316742 0.0))
((0 . "LINE") (100 . "AcDbEntity") (8 . "SOLAR") (62 . 7) (370 . 13) (100 . "AcDbLine") (10 15268.853699095
8178.7330316742 0.0) (11 15547.8883823529 8178.7330316742 0.0))
((0 . "LINE") (100 . "AcDbEntity") (8 . "SOLAR") (62 . 7) (370 . 13) (100 . "AcDbLine") (10 15547.8883823529
8178.7330316742 0.0) (11 15805.9954751131 8178.7330316742 0.0))
((0 . "LINE") (100 . "AcDbEntity") (8 . "SOLAR") (62 . 7) (370 . 13) (100 . "AcDbLine") (10 15805.9954751131
8178.7330316742 0.0) (11 15797.6131221719 8165.4977375566 0.0))
((0 . "LINE") (100 . "AcDbEntity") (8 . "SOLAR") (62 . 7) (370 . 13) (100 . "AcDbLine") (10 15797.6131221719
8165.4977375566 0.0) (11 15760.8597285068 8107.4660633484 0.0))
((0 . "LINE") (100 . "AcDbEntity") (8 . "SOLAR") (62 . 7) (370 . 13) (100 . "AcDbLine") (10 15760.8597285068
8107.4660633484 0.0) (11 15733.2946832579 8063.9423076923 0.0))
((0 . "LINE") (100 . "AcDbEntity") (8 . "SOLAR") (62 . 7) (370 . 13) (100 . "AcDbLine") (10 15733.2946832579
8063.9423076923 0.0) (11 15698.5831447964 8009.1346153846 0.0))
((0 . "LINE") (100 . "AcDbEntity") (8 . "SOLAR") (62 . 7) (370 . 13) (100 . "AcDbLine") (10 15698.5831447964
8009.1346153846 0.0) (11 15677.1436651584 7975.2828054299 0.0))
((0 . "LINE") (100 . "AcDbEntity") (8 . "SOLAR") (62 . 7) (370 . 13) (100 . "AcDbLine") (10 15677.1436651584
7975.2828054299 0.0) (11 15655.7041855204 7941.4309954751 0.0))
((0 . "LINE") (100 . "AcDbEntity") (8 . "SOLAR") (62 . 7) (370 . 13) (100 . "AcDbLine") (10 15655.7041855204
7941.4309954751 0.0) (11 15634.0497737557 7907.2398190045 0.0))
((0 . "LINE") (100 . "AcDbEntity") (8 . "SOLAR") (62 . 7) (370 . 13) (100 . "AcDbLine") (10 15634.0497737557
7907.2398190045 0.0) (11 15375.9426809955 7907.2398190045 0.0))
((0 . "LINE") (100 . "AcDbEntity") (8 . "SOLAR") (62 . 7) (370 . 13) (100 . "AcDbLine") (10 15375.9426809955
7907.2398190045 0.0) (11 15096.9079977376 7907.2398190045 0.0))
((0 . "LINE") (100 . "AcDbEntity") (8 . "SOLAR") (62 . 7) (370 . 13) (100 . "AcDbLine") (10 15096.9079977376
7907.2398190045 0.0) (11 14838.8009049774 7907.2398190045 0.0))
((0 . "LINE") (100 . "AcDbEntity") (8 . "SOLAR") (62 . 7) (370 . 13) (100 . "AcDbLine") (10 14838.8009049774
7907.2398190045 0.0) (11 14860.4553167421 7941.4309954751 0.0))
((0 . "LINE") (100 . "AcDbEntity") (8 . "SOLAR") (62 . 7) (370 . 13) (100 . "AcDbLine") (10 14860.4553167421
7941.4309954751 0.0) (11 14881.8947963801 7975.2828054299 0.0))
((0 . "LINE") (100 . "AcDbEntity") (8 . "SOLAR") (62 . 7) (370 . 13) (100 . "AcDbLine") (10 14881.8947963801
7975.2828054299 0.0) (11 14903.3342760181 8009.1346153846 0.0))
((0 . "LINE") (100 . "AcDbEntity") (8 . "SOLAR") (62 . 7) (370 . 13) (100 . "AcDbLine") (10 14903.3342760181
8009.1346153846 0.0) (11 14938.0458144796 8063.9423076923 0.0))
((0 . "LINE") (100 . "AcDbEntity") (8 . "SOLAR") (62 . 7) (370 . 13) (100 . "AcDbLine") (10 14938.0458144796
8063.9423076923 0.0) (11 14965.6108597285 8107.4660633484 0.0))
((0 . "LINE") (100 . "AcDbEntity") (8 . "SOLAR") (62 . 7) (370 . 13) (100 . "AcDbLine") (10 14965.6108597285
8107.4660633484 0.0) (11 15002.3642533937 8165.4977375566 0.0))
((0 . "LINE") (100 . "AcDbEntity") (8 . "SOLAR") (62 . 7) (370 . 13) (100 . "AcDbLine") (10 15002.3642533937
8165.4977375566 0.0) (11 15010.7466063348 8178.7330316742 0.0))
((0 . "LINE") (100 . "AcDbEntity") (8 . "SOLAR") (62 . 7) (370 . 13) (100 . "AcDbLine") (10 15268.853699095
8178.7330316742 0.0) (11 15260.4713461538 8165.4977375566 0.0))
((0 . "LINE") (100 . "AcDbEntity") (8 . "SOLAR") (62 . 7) (370 . 13) (100 . "AcDbLine") (10 15260.4713461538
8165.4977375566 0.0) (11 15223.7179524887 8107.4660633484 0.0))
((0 . "LINE") (100 . "AcDbEntity") (8 . "SOLAR") (62 . 7) (370 . 13) (100 . "AcDbLine") (10 15223.7179524887
8107.4660633484 0.0) (11 15196.1529072398 8063.9423076923 0.0))
((0 . "LINE") (100 . "AcDbEntity") (8 . "SOLAR") (62 . 7) (370 . 13) (100 . "AcDbLine") (10 15196.1529072398
8063.9423076923 0.0) (11 15161.4413687783 8009.1346153846 0.0))
((0 . "LINE") (100 . "AcDbEntity") (8 . "SOLAR") (62 . 7) (370 . 13) (100 . "AcDbLine") (10 15161.4413687783
8009.1346153846 0.0) (11 15140.0018891403 7975.2828054299 0.0))
((0 . "LINE") (100 . "AcDbEntity") (8 . "SOLAR") (62 . 7) (370 . 13) (100 . "AcDbLine") (10 15140.0018891403
7975.2828054299 0.0) (11 15118.5624095023 7941.4309954751 0.0))
((0 . "LINE") (100 . "AcDbEntity") (8 . "SOLAR") (62 . 7) (370 . 13) (100 . "AcDbLine") (10 15118.5624095023
7941.4309954751 0.0) (11 15096.9079977376 7907.2398190045 0.0))
((0 . "LINE") (100 . "AcDbEntity") (8 . "SOLAR") (62 . 7) (370 . 13) (100 . "AcDbLine") (10 15547.8883823529
8178.7330316742 0.0) (11 15539.5060294118 8165.4977375566 0.0))
((0 . "LINE") (100 . "AcDbEntity") (8 . "SOLAR") (62 . 7) (370 . 13) (100 . "AcDbLine") (10 15539.5060294118
8165.4977375566 0.0) (11 15502.7526357466 8107.4660633484 0.0))
((0 . "LINE") (100 . "AcDbEntity") (8 . "SOLAR") (62 . 7) (370 . 13) (100 . "AcDbLine") (10 15502.7526357466
8107.4660633484 0.0) (11 15475.1875904977 8063.9423076923 0.0))
((0 . "LINE") (100 . "AcDbEntity") (8 . "SOLAR") (62 . 7) (370 . 13) (100 . "AcDbLine") (10 15475.1875904977
8063.9423076923 0.0) (11 15440.4760520362 8009.1346153846 0.0))
((0 . "LINE") (100 . "AcDbEntity") (8 . "SOLAR") (62 . 7) (370 . 13) (100 . "AcDbLine") (10 15440.4760520362
8009.1346153846 0.0) (11 15419.0365723982 7975.2828054299 0.0))
((0 . "LINE") (100 . "AcDbEntity") (8 . "SOLAR") (62 . 7) (370 . 13) (100 . "AcDbLine") (10 15419.0365723982
7975.2828054299 0.0) (11 15397.5970927602 7941.4309954751 0.0))
((0 . "LINE") (100 . "AcDbEntity") (8 . "SOLAR") (62 . 7) (370 . 13) (100 . "AcDbLine") (10 15397.5970927602
7941.4309954751 0.0) (11 15375.9426809955 7907.2398190045 0.0))
((0 . "LINE") (100 . "AcDbEntity") (8 . "SOLAR") (62 . 7) (370 . 13) (100 . "AcDbLine") (10 15002.3642533937
8165.4977375566 0.0) (11 15260.4713461538 8165.4977375566 0.0))
((0 . "LINE") (100 . "AcDbEntity") (8 . "SOLAR") (62 . 7) (370 . 13) (100 . "AcDbLine") (10 15260.4713461538
8165.4977375566 0.0) (11 15539.5060294118 8165.4977375566 0.0))
((0 . "LINE") (100 . "AcDbEntity") (8 . "SOLAR") (62 . 7) (370 . 13) (100 . "AcDbLine") (10 15539.5060294118
8165.4977375566 0.0) (11 15797.6131221719 8165.4977375566 0.0))
((0 . "LINE") (100 . "AcDbEntity") (8 . "SOLAR") (62 . 7) (370 . 13) (100 . "AcDbLine") (10 14965.6108597285
8107.4660633484 0.0) (11 15223.7179524887 8107.4660633484 0.0))
((0 . "LINE") (100 . "AcDbEntity") (8 . "SOLAR") (62 . 7) (370 . 13) (100 . "AcDbLine") (10 15223.7179524887
8107.4660633484 0.0) (11 15502.7526357466 8107.4660633484 0.0))
((0 . "LINE") (100 . "AcDbEntity") (8 . "SOLAR") (62 . 7) (370 . 13) (100 . "AcDbLine") (10 15502.7526357466
8107.4660633484 0.0) (11 15760.8597285068 8107.4660633484 0.0))
((0 . "LINE") (100 . "AcDbEntity") (8 . "SOLAR") (62 . 7) (370 . 13) (100 . "AcDbLine") (10 14938.0458144796
8063.9423076923 0.0) (11 15196.1529072398 8063.9423076923 0.0))
((0 . "LINE") (100 . "AcDbEntity") (8 . "SOLAR") (62 . 7) (370 . 13) (100 . "AcDbLine") (10 15196.1529072398
8063.9423076923 0.0) (11 15475.1875904977 8063.9423076923 0.0))
((0 . "LINE") (100 . "AcDbEntity") (8 . "SOLAR") (62 . 7) (370 . 13) (100 . "AcDbLine") (10 15475.1875904977
8063.9423076923 0.0) (11 15733.2946832579 8063.9423076923 0.0))
((0 . "LINE") (100 . "AcDbEntity") (8 . "SOLAR") (62 . 7) (370 . 13) (100 . "AcDbLine") (10 14903.3342760181
8009.1346153846 0.0) (11 15161.4413687783 8009.1346153846 0.0))
((0 . "LINE") (100 . "AcDbEntity") (8 . "SOLAR") (62 . 7) (370 . 13) (100 . "AcDbLine") (10 15161.4413687783
8009.1346153846 0.0) (11 15440.4760520362 8009.1346153846 0.0))
((0 . "LINE") (100 . "AcDbEntity") (8 . "SOLAR") (62 . 7) (370 . 13) (100 . "AcDbLine") (10 15440.4760520362
8009.1346153846 0.0) (11 15698.5831447964 8009.1346153846 0.0))
((0 . "LINE") (100 . "AcDbEntity") (8 . "SOLAR") (62 . 7) (370 . 13) (100 . "AcDbLine") (10 14881.8947963801
7975.2828054299 0.0) (11 15140.0018891403 7975.2828054299 0.0))
((0 . "LINE") (100 . "AcDbEntity") (8 . "SOLAR") (62 . 7) (370 . 13) (100 . "AcDbLine") (10 15140.0018891403
7975.2828054299 0.0) (11 15419.0365723982 7975.2828054299 0.0))
((0 . "LINE") (100 . "AcDbEntity") (8 . "SOLAR") (62 . 7) (370 . 13) (100 . "AcDbLine") (10 15419.0365723982
7975.2828054299 0.0) (11 15677.1436651584 7975.2828054299 0.0))
((0 . "LINE") (100 . "AcDbEntity") (8 . "SOLAR") (62 . 7) (370 . 13) (100 . "AcDbLine") (10 14860.4553167421
7941.4309954751 0.0) (11 15118.5624095023 7941.4309954751 0.0))
((0 . "LINE") (100 . "AcDbEntity") (8 . "SOLAR") (62 . 7) (370 . 13) (100 . "AcDbLine") (10 15118.5624095023
7941.4309954751 0.0) (11 15397.5970927602 7941.4309954751 0.0))
((0 . "LINE") (100 . "AcDbEntity") (8 . "SOLAR") (62 . 7) (370 . 13) (100 . "AcDbLine") (10 15397.5970927602
7941.4309954751 0.0) (11 15655.7041855204 7941.4309954751 0.0))
((0 . "LINE") (100 . "AcDbEntity") (8 . "MASONRY") (62 . 7) (370 . 13) (100 . "AcDbLine") (10 2801.6586651584
220.5882352941 0.0) (11 2801.6586651584 226.2015384615 0.0))
((0 . "LINE") (100 . "AcDbEntity") (8 . "MASONRY") (62 . 7) (370 . 13) (100 . "AcDbLine") (10 2797.8871153846
348.7758710407 0.0) (11 2797.8871153846 765.4609502262 0.0))
((0 . "LINE") (100 . "AcDbEntity") (8 . "MASONRY") (62 . 7) (370 . 13) (100 . "AcDbLine") (10 2794.1176470588
3580.3167420814 0.0) (11 2794.1176470588 3012.8202828054 0.0))
((0 . "LINE") (100 . "AcDbEntity") (8 . "MASONRY") (62 . 7) (370 . 13) (100 . "AcDbLine") (10 2794.1176470588
2812.9715723982 0.0) (11 2794.1176470588 2417.0439705882 0.0))
((0 . "LINE") (100 . "AcDbEntity") (8 . "MASONRY") (62 . 7) (370 . 13) (100 . "AcDbLine") (10 2794.1176470588
2417.0439705882 0.0) (11 2794.1176470588 2398.1900452489 0.0))
((0 . "LINE") (100 . "AcDbEntity") (8 . "MASONRY") (62 . 7) (370 . 13) (100 . "AcDbLine") (10 2794.1176470588
2812.9715723982 0.0) (11 2794.1176470588 3012.8202828054 0.0))
((0 . "LINE") (100 . "AcDbEntity") (8 . "MASONRY") (62 . 7) (370 . 13) (100 . "AcDbLine") (10 2794.1176470588
1259.4259276018 0.0) (11 2794.1176470588 1293.3625791855 0.0))
((0 . "LINE") (100 . "AcDbEntity") (8 . "MASONRY") (62 . 7) (370 . 13) (100 . "AcDbLine") (10 2794.1176470588
1259.4259276018 0.0) (11 2794.1176470588 1180.2404072398 0.0))
((0 . "LINE") (100 . "AcDbEntity") (8 . "MASONRY") (62 . 7) (370 . 13) (100 . "AcDbLine") (10 2794.1176470588
1180.2404072398 0.0) (11 2794.1176470588 1150.0763348416 0.0))
((0 . "LINE") (100 . "AcDbEntity") (8 . "MASONRY") (62 . 7) (370 . 13) (100 . "AcDbLine") (10 2846.9082239819
1866.5158371041 0.0) (11 2869.532658371 1866.5158371041 0.0))
((0 . "LINE") (100 . "AcDbEntity") (8 . "MASONRY") (62 . 7) (370 . 13) (100 . "AcDbLine") (10 2901.5837104072
1168.9295701357 0.0) (11 2846.9082239819 1168.9295701357 0.0))
((0 . "LINE") (100 . "AcDbEntity") (8 . "MASONRY") (62 . 7) (370 . 13) (100 . "AcDbLine") (10 2850.6787330317
3470.9650791855 0.0) (11 3016.5911312217 3470.9650791855 0.0))
((0 . "LINE") (100 . "AcDbEntity") (8 . "MASONRY") (62 . 7) (370 . 13) (100 . "AcDbLine") (10 2933.6351131222
3355.9579977376 0.0) (11 2850.6787330317 3355.9579977376 0.0))
((0 . "LINE") (100 . "AcDbEntity") (8 . "MASONRY") (62 . 7) (370 . 13) (100 . "AcDbLine") (10 2899.6984615385
2754.5248868778 0.0) (11 2850.6787330317 2754.5248868778 0.0))
((0 . "LINE") (100 . "AcDbEntity") (8 . "MASONRY") (62 . 7) (370 . 13) (100 . "AcDbLine") (10 2850.6787330317
2677.2249660633 0.0) (11 2850.6787330317 2684.7659841629 0.0))
((0 . "LINE") (100 . "AcDbEntity") (8 . "MASONRY") (62 . 7) (370 . 13) (100 . "AcDbLine") (10 2850.6787330317
2669.6832579186 0.0) (11 2850.6787330317 2677.2249660633 0.0))
((0 . "LINE") (100 . "AcDbEntity") (8 . "MASONRY") (62 . 7) (370 . 13) (100 . "AcDbLine") (10 2850.6787330317
2501.8855995475 0.0) (11 3344.6454298643 2501.8855995475 0.0))
((0 . "LINE") (100 . "AcDbEntity") (8 . "MASONRY") (62 . 7) (370 . 13) (100 . "AcDbLine") (10 2850.6787330317
2378.1319909502 0.0) (11 2918.5520361991 2378.1319909502 0.0))
((0 . "LINE") (100 . "AcDbEntity") (8 . "MASONRY") (62 . 7) (370 . 13) (100 . "AcDbLine") (10 2918.5520361991
2378.1319909502 0.0) (11 2933.6351131222 2378.1319909502 0.0))
((0 . "LINE") (100 . "AcDbEntity") (8 . "MASONRY") (62 . 7) (370 . 13) (100 . "AcDbLine") (10 2922.4775452489
2279.4117647059 0.0) (11 2850.6787330317 2279.4117647059 0.0))
((0 . "LINE") (100 . "AcDbEntity") (8 . "MASONRY") (62 . 7) (370 . 13) (100 . "AcDbLine") (10 2911.010678733
2230.3916968326 0.0) (11 2850.6787330317 2230.3916968326 0.0))
((0 . "LINE") (100 . "AcDbEntity") (8 . "MASONRY") (62 . 7) (370 . 13) (100 . "AcDbLine") (10 2850.6787330317
1966.4367420814 0.0) (11 3084.4644343891 1966.4367420814 0.0))
((0 . "LINE") (100 . "AcDbEntity") (8 . "MASONRY") (62 . 7) (370 . 13) (100 . "AcDbLine") (10 3084.4644343891
1966.4367420814 0.0) (11 3159.8794570136 1966.4367420814 0.0))
((0 . "LINE") (100 . "AcDbEntity") (8 . "MASONRY") (62 . 7) (370 . 13) (100 . "AcDbLine") (10 3159.8794570136
1966.4367420814 0.0) (11 3574.6606334842 1966.4367420814 0.0))
((0 . "LINE") (100 . "AcDbEntity") (8 . "MASONRY") (62 . 7) (370 . 13) (100 . "AcDbLine") (10 2899.695 1723.2268325792
0.0) (11 2899.695 1734.4624095023 0.0))
((0 . "LINE") (100 . "AcDbEntity") (8 . "MASONRY") (62 . 7) (370 . 13) (100 . "AcDbLine") (10 2899.695 1734.4624095023
0.0) (11 2850.6787330317 1734.4624095023 0.0))
((0 . "LINE") (100 . "AcDbEntity") (8 . "MASONRY") (62 . 7) (370 . 13) (100 . "AcDbLine") (10 3141.025520362
1670.4383257919 0.0) (11 2850.6787330317 1670.4383257919 0.0))
((0 . "LINE") (100 . "AcDbEntity") (8 . "MASONRY") (62 . 7) (370 . 13) (100 . "AcDbLine") (10 2850.6787330317
1457.3911085973 0.0) (11 3027.9033484163 1457.3911085973 0.0))
((0 . "LINE") (100 . "AcDbEntity") (8 . "MASONRY") (62 . 7) (370 . 13) (100 . "AcDbLine") (10 2892.1567420814
1395.1739140271 0.0) (11 2850.6787330317 1395.1739140271 0.0))
((0 . "LINE") (100 . "AcDbEntity") (8 . "MASONRY") (62 . 7) (370 . 13) (100 . "AcDbLine") (10 2854.4492420814
3263.500780543 0.0) (11 3178.7330316742 3263.500780543 0.0))
((0 . "LINE") (100 . "AcDbEntity") (8 . "MASONRY") (62 . 7) (370 . 13) (100 . "AcDbLine") (10 3178.7330316742
3263.500780543 0.0) (11 3229.6380090498 3263.500780543 0.0))
((0 . "LINE") (100 . "AcDbEntity") (8 . "MASONRY") (62 . 7) (370 . 13) (100 . "AcDbLine") (10 2961.9153054299
3190.0452488688 0.0) (11 2854.4492420814 3190.0452488688 0.0))
((0 . "LINE") (100 . "AcDbEntity") (8 . "MASONRY") (62 . 7) (370 . 13) (100 . "AcDbLine") (10 2895.92760181
2677.2249660633 0.0) (11 2850.6787330317 2677.2249660633 0.0))
((0 . "LINE") (100 . "AcDbEntity") (8 . "MASONRY") (62 . 7) (370 . 13) (100 . "AcDbLine") (10 2899.620780543
2643.2883144796 0.0) (11 2899.620780543 2625.036459276 0.0))
((0 . "LINE") (100 . "AcDbEntity") (8 . "MASONRY") (62 . 7) (370 . 13) (100 . "AcDbLine") (10 2899.620780543
2625.036459276 0.0) (11 2854.4492420814 2625.036459276 0.0))
((0 . "LINE") (100 . "AcDbEntity") (8 . "MASONRY") (62 . 7) (370 . 13) (100 . "AcDbLine") (10 3259.8041515837
2576.6191402715 0.0) (11 2954.4481674208 2576.6191402715 0.0))
((0 . "LINE") (100 . "AcDbEntity") (8 . "MASONRY") (62 . 7) (370 . 13) (100 . "AcDbLine") (10 2954.4481674208
2576.6191402715 0.0) (11 2954.4481674208 2597.9621153846 0.0))
((0 . "LINE") (100 . "AcDbEntity") (8 . "MASONRY") (62 . 7) (370 . 13) (100 . "AcDbLine") (10 2954.4481674208
2597.9621153846 0.0) (11 2854.4492420814 2597.9621153846 0.0))
((0 . "LINE") (100 . "AcDbEntity") (8 . "MASONRY") (62 . 7) (370 . 13) (100 . "AcDbLine") (10 2978.8839819005
1606.334841629 0.0) (11 2854.4492420814 1606.334841629 0.0))
((0 . "LINE") (100 . "AcDbEntity") (8 . "MASONRY") (62 . 7) (370 . 13) (100 . "AcDbLine") (10 2854.4492420814
1027.5268552036 0.0) (11 2924.2081447964 1027.5268552036 0.0))
((0 . "LINE") (100 . "AcDbEntity") (8 . "MASONRY") (62 . 7) (370 . 13) (100 . "AcDbLine") (10 3095.7766515837
984.1628959276 0.0) (11 3095.7766515837 960.2556221719 0.0))
((0 . "LINE") (100 . "AcDbEntity") (8 . "MASONRY") (62 . 7) (370 . 13) (100 . "AcDbLine") (10 3095.7766515837
960.2556221719 0.0) (11 2854.4492420814 960.2556221719 0.0))
((0 . "LINE") (100 . "AcDbEntity") (8 . "MASONRY") (62 . 7) (370 . 13) (100 . "AcDbLine") (10 2854.4492420814
785.5307466063 0.0) (11 2998.3662104072 785.5307466063 0.0))
((0 . "LINE") (100 . "AcDbEntity") (8 . "MASONRY") (62 . 7) (370 . 13) (100 . "AcDbLine") (10 3071.5065497738
780.5298642534 0.0) (11 3182.5038914027 780.5298642534 0.0))
((0 . "LINE") (100 . "AcDbEntity") (8 . "MASONRY") (62 . 7) (370 . 13) (100 . "AcDbLine") (10 2877.0736764706
584.4640950226 0.0) (11 2854.4492420814 584.4640950226 0.0))
((0 . "LINE") (100 . "AcDbEntity") (8 . "MASONRY") (62 . 7) (370 . 13) (100 . "AcDbLine") (10 2858.2204411765
2973.2282126697 0.0) (11 3054.2986425339 2973.2282126697 0.0))
((0 . "LINE") (100 . "AcDbEntity") (8 . "MASONRY") (62 . 7) (370 . 13) (100 . "AcDbLine") (10 3054.2986425339
2899.6981108597 0.0) (11 2858.2204411765 2899.6981108597 0.0))
((0 . "LINE") (100 . "AcDbEntity") (8 . "MASONRY") (62 . 7) (370 . 13) (100 . "AcDbLine") (10 3120.2863461538
2820.5125904977 0.0) (11 2858.2204411765 2820.5125904977 0.0))
((0 . "LINE") (100 . "AcDbEntity") (8 . "MASONRY") (62 . 7) (370 . 13) (100 . "AcDbLine") (10 2941.1764705882
720.212081448 0.0) (11 2858.2204411765 720.212081448 0.0))
((0 . "LINE") (100 . "AcDbEntity") (8 . "MASONRY") (62 . 7) (370 . 13) (100 . "AcDbLine") (10 2857.3035294118
226.0779524887 0.0) (11 2857.3035294118 220.5882352941 0.0))
((0 . "LINE") (100 . "AcDbEntity") (8 . "MASONRY") (62 . 7) (370 . 13) (100 . "AcDbLine") (10 3344.6454298643
3046.7569343891 0.0) (11 2861.9909502262 3046.7569343891 0.0))
((0 . "LINE") (100 . "AcDbEntity") (8 . "MASONRY") (62 . 7) (370 . 13) (100 . "AcDbLine") (10 2905.354219457
1266.9683257919 0.0) (11 2861.9909502262 1266.9683257919 0.0))
((0 . "LINE") (100 . "AcDbEntity") (8 . "MASONRY") (62 . 7) (370 . 13) (100 . "AcDbLine") (10 2897.8132013575
3001.5080656109 0.0) (11 2897.8132013575 2993.9670475113 0.0))
((0 . "LINE") (100 . "AcDbEntity") (8 . "MASONRY") (62 . 7) (370 . 13) (100 . "AcDbLine") (10 2905.354219457
1332.956719457 0.0) (11 2895.92760181 1332.956719457 0.0))
((0 . "LINE") (100 . "AcDbEntity") (8 . "MASONRY") (62 . 7) (370 . 13) (100 . "AcDbLine") (10 2903.4693099548
3525.6412556561 0.0) (11 2903.4693099548 3518.0995475113 0.0))
((0 . "LINE") (100 . "AcDbEntity") (8 . "MASONRY") (62 . 7) (370 . 13) (100 . "AcDbLine") (10 2899.6984615385
2754.5248868778 0.0) (11 2899.6984615385 2703.6199095023 0.0))
((0 . "LINE") (100 . "AcDbEntity") (8 . "MASONRY") (62 . 7) (370 . 13) (100 . "AcDbLine") (10 2899.6984615385
2754.5248868778 0.0) (11 3110.8597285068 2754.5248868778 0.0))
((0 . "LINE") (100 . "AcDbEntity") (8 . "MASONRY") (62 . 7) (370 . 13) (100 . "AcDbLine") (10 3110.8597285068
2754.5248868778 0.0) (11 3220.211040724 2754.5248868778 0.0))
((0 . "LINE") (100 . "AcDbEntity") (8 . "MASONRY") (62 . 7) (370 . 13) (100 . "AcDbLine") (10 2914.7811764706
2058.8235294118 0.0) (11 2899.6984615385 2058.8235294118 0.0))
((0 . "LINE") (100 . "AcDbEntity") (8 . "MASONRY") (62 . 7) (370 . 13) (100 . "AcDbLine") (10 2905.354219457
1225.4892760181 0.0) (11 2905.354219457 1265.0088461538 0.0))
((0 . "LINE") (100 . "AcDbEntity") (8 . "MASONRY") (62 . 7) (370 . 13) (100 . "AcDbLine") (10 2905.354219457
1265.0088461538 0.0) (11 2905.354219457 1266.9683257919 0.0))
((0 . "LINE") (100 . "AcDbEntity") (8 . "MASONRY") (62 . 7) (370 . 13) (100 . "AcDbLine") (10 2901.5837104072
1168.9295701357 0.0) (11 2924.2081447964 1168.9295701357 0.0))
((0 . "LINE") (100 . "AcDbEntity") (8 . "MASONRY") (62 . 7) (370 . 13) (100 . "AcDbLine") (10 2901.5837104072
1168.9295701357 0.0) (11 2901.5837104072 1187.7828054299 0.0))
((0 . "LINE") (100 . "AcDbEntity") (8 . "MASONRY") (62 . 7) (370 . 13) (100 . "AcDbLine") (10 2899.6984615385
588.2352941176 0.0) (11 2918.5520361991 588.2352941176 0.0))
((0 . "LINE") (100 . "AcDbEntity") (8 . "MASONRY") (62 . 7) (370 . 13) (100 . "AcDbLine") (10 3044.8716742081
1376.320678733 0.0) (11 3044.8716742081 1391.3253846154 0.0))
((0 . "LINE") (100 . "AcDbEntity") (8 . "MASONRY") (62 . 7) (370 . 13) (100 . "AcDbLine") (10 3044.8716742081
1391.3253846154 0.0) (11 2903.468959276 1391.3253846154 0.0))
((0 . "LINE") (100 . "AcDbEntity") (8 . "MASONRY") (62 . 7) (370 . 13) (100 . "AcDbLine") (10 2905.354219457
1266.9683257919 0.0) (11 2905.354219457 1332.956719457 0.0))
((0 . "LINE") (100 . "AcDbEntity") (8 . "MASONRY") (62 . 7) (370 . 13) (100 . "AcDbLine") (10 2937.4056108597
1332.956719457 0.0) (11 2905.354219457 1332.956719457 0.0))
((0 . "LINE") (100 . "AcDbEntity") (8 . "MASONRY") (62 . 7) (370 . 13) (100 . "AcDbLine") (10 2905.354219457
1265.0088461538 0.0) (11 3146.681979638 1265.0088461538 0.0))
((0 . "LINE") (100 . "AcDbEntity") (8 . "MASONRY") (62 . 7) (370 . 13) (100 . "AcDbLine") (10 2914.7811764706
2058.8235294118 0.0) (11 2926.0933936652 2058.8235294118 0.0))
((0 . "LINE") (100 . "AcDbEntity") (8 . "MASONRY") (62 . 7) (370 . 13) (100 . "AcDbLine") (10 2914.7811764706
2058.8235294118 0.0) (11 2914.7811764706 2100.3018891403 0.0))
((0 . "LINE") (100 . "AcDbEntity") (8 . "MASONRY") (62 . 7) (370 . 13) (100 . "AcDbLine") (10 3131.5985633484
1858.9741289593 0.0) (11 2911.010678733 1858.9741289593 0.0))
((0 . "LINE") (100 . "AcDbEntity") (8 . "MASONRY") (62 . 7) (370 . 13) (100 . "AcDbLine") (10 2914.7811764706
2115.3846153846 0.0) (11 2914.7811764706 2100.3018891403 0.0))
((0 . "LINE") (100 . "AcDbEntity") (8 . "MASONRY") (62 . 7) (370 . 13) (100 . "AcDbLine") (10 2922.4775452489
2279.4117647059 0.0) (11 2922.4775452489 2265.0788574661 0.0))
((0 . "LINE") (100 . "AcDbEntity") (8 . "MASONRY") (62 . 7) (370 . 13) (100 . "AcDbLine") (10 2922.4775452489
2265.0788574661 0.0) (11 3088.2352941176 2265.0788574661 0.0))
((0 . "LINE") (100 . "AcDbEntity") (8 . "MASONRY") (62 . 7) (370 . 13) (100 . "AcDbLine") (10 3088.2352941176
2265.0788574661 0.0) (11 3088.2352941176 2281.2973642534 0.0))
((0 . "LINE") (100 . "AcDbEntity") (8 . "MASONRY") (62 . 7) (370 . 13) (100 . "AcDbLine") (10 2922.4775452489
2279.4117647059 0.0) (11 2922.4775452489 2318.9299547511 0.0))
((0 . "LINE") (100 . "AcDbEntity") (8 . "MASONRY") (62 . 7) (370 . 13) (100 . "AcDbLine") (10 2922.4775452489
2318.9299547511 0.0) (11 2952.4886877828 2318.9299547511 0.0))
((0 . "LINE") (100 . "AcDbEntity") (8 . "MASONRY") (62 . 7) (370 . 13) (100 . "AcDbLine") (10 3180.6186312217
2156.8629751131 0.0) (11 2918.5520361991 2156.8629751131 0.0))
((0 . "LINE") (100 . "AcDbEntity") (8 . "MASONRY") (62 . 7) (370 . 13) (100 . "AcDbLine") (10 2978.8839819005
2100.3018891403 0.0) (11 2914.7811764706 2100.3018891403 0.0))
((0 . "LINE") (100 . "AcDbEntity") (8 . "MASONRY") (62 . 7) (370 . 13) (100 . "AcDbLine") (10 2924.2081447964
1168.9295701357 0.0) (11 2924.2081447964 1142.5339366516 0.0))
((0 . "LINE") (100 . "AcDbEntity") (8 . "MASONRY") (62 . 7) (370 . 13) (100 . "AcDbLine") (10 2922.3228959276
1093.35989819 0.0) (11 2933.6416628959 1093.35989819 0.0))
((0 . "LINE") (100 . "AcDbEntity") (8 . "MASONRY") (62 . 7) (370 . 13) (100 . "AcDbLine") (10 2933.6416628959
1093.35989819 0.0) (11 2975.1131221719 1093.35989819 0.0))
((0 . "LINE") (100 . "AcDbEntity") (8 . "MASONRY") (62 . 7) (370 . 13) (100 . "AcDbLine") (10 2924.2081447964
1044.493800905 0.0) (11 2924.2081447964 1027.5268552036 0.0))
((0 . "LINE") (100 . "AcDbEntity") (8 . "MASONRY") (62 . 7) (370 . 13) (100 . "AcDbLine") (10 2933.6351131222
3329.5623642534 0.0) (11 2926.0933936652 3329.5623642534 0.0))
((0 . "LINE") (100 . "AcDbEntity") (8 . "MASONRY") (62 . 7) (370 . 13) (100 . "AcDbLine") (10 2924.2081447964
1168.9295701357 0.0) (11 3046.7572850679 1168.9295701357 0.0))
((0 . "LINE") (100 . "AcDbEntity") (8 . "MASONRY") (62 . 7) (370 . 13) (100 . "AcDbLine") (10 2988.310938914
1027.5268552036 0.0) (11 2924.2081447964 1027.5268552036 0.0))
((0 . "LINE") (100 . "AcDbEntity") (8 . "MASONRY") (62 . 7) (370 . 13) (100 . "AcDbLine") (10 2933.6351131222
3355.9579977376 0.0) (11 2933.6351131222 3329.5623642534 0.0))
((0 . "LINE") (100 . "AcDbEntity") (8 . "MASONRY") (62 . 7) (370 . 13) (100 . "AcDbLine") (10 2933.6351131222
3355.9579977376 0.0) (11 2933.6351131222 3413.8758031674 0.0))
((0 . "LINE") (100 . "AcDbEntity") (8 . "MASONRY") (62 . 7) (370 . 13) (100 . "AcDbLine") (10 2933.6351131222
3413.8758031674 0.0) (11 3024.1328506787 3413.8758031674 0.0))
((0 . "LINE") (100 . "AcDbEntity") (8 . "MASONRY") (62 . 7) (370 . 13) (100 . "AcDbLine") (10 2933.6351131222
3329.5623642534 0.0) (11 3229.6380090498 3329.5623642534 0.0))
((0 . "LINE") (100 . "AcDbEntity") (8 . "MASONRY") (62 . 7) (370 . 13) (100 . "AcDbLine") (10 2933.6351131222
2378.1319909502 0.0) (11 3363.4993665158 2378.1319909502 0.0))
((0 . "LINE") (100 . "AcDbEntity") (8 . "MASONRY") (62 . 7) (370 . 13) (100 . "AcDbLine") (10 3363.4993665158
2378.1319909502 0.0) (11 3386.123800905 2378.1319909502 0.0))
((0 . "LINE") (100 . "AcDbEntity") (8 . "MASONRY") (62 . 7) (370 . 13) (100 . "AcDbLine") (10 3386.123800905
2378.1319909502 0.0) (11 3518.0995475113 2378.1319909502 0.0))
((0 . "LINE") (100 . "AcDbEntity") (8 . "MASONRY") (62 . 7) (370 . 13) (100 . "AcDbLine") (10 2933.6351131222
2360.4828846154 0.0) (11 2933.6351131222 2378.1319909502 0.0))
((0 . "LINE") (100 . "AcDbEntity") (8 . "MASONRY") (62 . 7) (370 . 13) (100 . "AcDbLine") (10 3318.2504977376
2643.2848642534 0.0) (11 3235.300678733 2643.2848642534 0.0))
((0 . "LINE") (100 . "AcDbEntity") (8 . "MASONRY") (62 . 7) (370 . 13) (100 . "AcDbLine") (10 3235.300678733
2643.2848642534 0.0) (11 3208.8988235294 2643.2848642534 0.0))
((0 . "LINE") (100 . "AcDbEntity") (8 . "MASONRY") (62 . 7) (370 . 13) (100 . "AcDbLine") (10 3208.8988235294
2643.2848642534 0.0) (11 2937.4056108597 2643.2848642534 0.0))
((0 . "LINE") (100 . "AcDbEntity") (8 . "MASONRY") (62 . 7) (370 . 13) (100 . "AcDbLine") (10 2939.2908710407
1745.8512669683 0.0) (11 2939.2908710407 1757.1634841629 0.0))
((0 . "LINE") (100 . "AcDbEntity") (8 . "MASONRY") (62 . 7) (370 . 13) (100 . "AcDbLine") (10 2937.4056108597
1332.956719457 0.0) (11 2937.4056108597 1342.3840271493 0.0))
((0 . "LINE") (100 . "AcDbEntity") (8 . "MASONRY") (62 . 7) (370 . 13) (100 . "AcDbLine") (10 2937.4056108597
1332.956719457 0.0) (11 3048.6425339367 1332.956719457 0.0))
((0 . "LINE") (100 . "AcDbEntity") (8 . "MASONRY") (62 . 7) (370 . 13) (100 . "AcDbLine") (10 2941.1764705882
1813.8799208145 0.0) (11 3122.1653846154 1813.8799208145 0.0))
((0 . "LINE") (100 . "AcDbEntity") (8 . "MASONRY") (62 . 7) (370 . 13) (100 . "AcDbLine") (10 3122.1653846154
1813.8799208145 0.0) (11 3133.4841628959 1813.8799208145 0.0))
((0 . "LINE") (100 . "AcDbEntity") (8 . "MASONRY") (62 . 7) (370 . 13) (100 . "AcDbLine") (10 2941.1764705882
739.0639366516 0.0) (11 2941.1764705882 720.212081448 0.0))
((0 . "LINE") (100 . "AcDbEntity") (8 . "MASONRY") (62 . 7) (370 . 13) (100 . "AcDbLine") (10 2941.1764705882
720.212081448 0.0) (11 2975.1131221719 720.212081448 0.0))
((0 . "LINE") (100 . "AcDbEntity") (8 . "MASONRY") (62 . 7) (370 . 13) (100 . "AcDbLine") (10 3061.84 842.7891742081
0.0) (11 3008.5681900452 842.7891742081 0.0))
((0 . "LINE") (100 . "AcDbEntity") (8 . "MASONRY") (62 . 7) (370 . 13) (100 . "AcDbLine") (10 2982.7756561086
842.0690497738 0.0) (11 2948.7178280543 842.0690497738 0.0))
((0 . "LINE") (100 . "AcDbEntity") (8 . "MASONRY") (62 . 7) (370 . 13) (100 . "AcDbLine") (10 2952.4886877828
2055.053020362 0.0) (11 3016.5911312217 2055.053020362 0.0))
((0 . "LINE") (100 . "AcDbEntity") (8 . "MASONRY") (62 . 7) (370 . 13) (100 . "AcDbLine") (10 2961.9153054299
3190.0452488688 0.0) (11 2961.9153054299 3174.9625226244 0.0))
((0 . "LINE") (100 . "AcDbEntity") (8 . "MASONRY") (62 . 7) (370 . 13) (100 . "AcDbLine") (10 2961.9153054299
3148.5668891403 0.0) (11 2961.9153054299 3156.1085972851 0.0))
((0 . "LINE") (100 . "AcDbEntity") (8 . "MASONRY") (62 . 7) (370 . 13) (100 . "AcDbLine") (10 2960.0300452489
3107.0885294118 0.0) (11 3280.5429864253 3107.0885294118 0.0))
((0 . "LINE") (100 . "AcDbEntity") (8 . "MASONRY") (62 . 7) (370 . 13) (100 . "AcDbLine") (10 3148.567239819
3190.0452488688 0.0) (11 2961.9153054299 3190.0452488688 0.0))
((0 . "LINE") (100 . "AcDbEntity") (8 . "MASONRY") (62 . 7) (370 . 13) (100 . "AcDbLine") (10 2965.6865045249
535.4440271493 0.0) (11 2965.6865045249 546.7562443439 0.0))
((0 . "LINE") (100 . "AcDbEntity") (8 . "MASONRY") (62 . 7) (370 . 13) (100 . "AcDbLine") (10 2978.8839819005
1632.7290950226 0.0) (11 2978.8839819005 1606.334841629 0.0))
((0 . "LINE") (100 . "AcDbEntity") (8 . "MASONRY") (62 . 7) (370 . 13) (100 . "AcDbLine") (10 3306.938280543
1606.334841629 0.0) (11 2978.8839819005 1606.334841629 0.0))
((0 . "LINE") (100 . "AcDbEntity") (8 . "MASONRY") (62 . 7) (370 . 13) (100 . "AcDbLine") (10 3042.9864253394
2326.5462330317 0.0) (11 2986.4253393665 2326.5462330317 0.0))
((0 . "LINE") (100 . "AcDbEntity") (8 . "MASONRY") (62 . 7) (370 . 13) (100 . "AcDbLine") (10 2986.4253393665
1743.9663574661 0.0) (11 3039.2155656109 1743.9663574661 0.0))
((0 . "LINE") (100 . "AcDbEntity") (8 . "MASONRY") (62 . 7) (370 . 13) (100 . "AcDbLine") (10 2986.4253393665
1099.0940271493 0.0) (11 3567.1192760181 1099.0940271493 0.0))
((0 . "LINE") (100 . "AcDbEntity") (8 . "MASONRY") (62 . 7) (370 . 13) (100 . "AcDbLine") (10 3567.1192760181
1099.0940271493 0.0) (11 3731.1464253394 1099.0940271493 0.0))
((0 . "LINE") (100 . "AcDbEntity") (8 . "MASONRY") (62 . 7) (370 . 13) (100 . "AcDbLine") (10 3054.2986425339
1027.5268552036 0.0) (11 2988.310938914 1027.5268552036 0.0))
((0 . "LINE") (100 . "AcDbEntity") (8 . "MASONRY") (62 . 7) (370 . 13) (100 . "AcDbLine") (10 2988.310938914
1027.5268552036 0.0) (11 2988.310938914 1055.8060180995 0.0))
((0 . "LINE") (100 . "AcDbEntity") (8 . "MASONRY") (62 . 7) (370 . 13) (100 . "AcDbLine") (10 3010.9353733032
588.2352941176 0.0) (11 3010.9353733032 580.6928959276 0.0))
((0 . "LINE") (100 . "AcDbEntity") (8 . "MASONRY") (62 . 7) (370 . 13) (100 . "AcDbLine") (10 3020.3619909502
2100.3018891403 0.0) (11 3254.1476923077 2100.3018891403 0.0))
((0 . "LINE") (100 . "AcDbEntity") (8 . "MASONRY") (62 . 7) (370 . 13) (100 . "AcDbLine") (10 3186.2743891403
3414.4046832579 0.0) (11 3039.2155656109 3414.4046832579 0.0))
((0 . "LINE") (100 . "AcDbEntity") (8 . "MASONRY") (62 . 7) (370 . 13) (100 . "AcDbLine") (10 3046.7572850679
3472.850678733 0.0) (11 3470.9654298643 3472.850678733 0.0))
((0 . "LINE") (100 . "AcDbEntity") (8 . "MASONRY") (62 . 7) (370 . 13) (100 . "AcDbLine") (10 3048.6425339367
1346.1538461538 0.0) (11 3048.6425339367 1332.956719457 0.0))
((0 . "LINE") (100 . "AcDbEntity") (8 . "MASONRY") (62 . 7) (370 . 13) (100 . "AcDbLine") (10 3048.6425339367
1332.956719457 0.0) (11 3320.1357466063 1332.956719457 0.0))
((0 . "LINE") (100 . "AcDbEntity") (8 . "MASONRY") (62 . 7) (370 . 13) (100 . "AcDbLine") (10 3054.2986425339
2899.6981108597 0.0) (11 3054.2986425339 2933.6347624434 0.0))
((0 . "LINE") (100 . "AcDbEntity") (8 . "MASONRY") (62 . 7) (370 . 13) (100 . "AcDbLine") (10 3054.2986425339
2899.6981108597 0.0) (11 3084.4644343891 2899.6981108597 0.0))
((0 . "LINE") (100 . "AcDbEntity") (8 . "MASONRY") (62 . 7) (370 . 13) (100 . "AcDbLine") (10 3061.8403506787
3525.6412556561 0.0) (11 3061.8403506787 3536.9534728507 0.0))
((0 . "LINE") (100 . "AcDbEntity") (8 . "MASONRY") (62 . 7) (370 . 13) (100 . "AcDbLine") (10 3295.6260633484
1447.963800905 0.0) (11 3076.9230769231 1447.963800905 0.0))
((0 . "LINE") (100 . "AcDbEntity") (8 . "MASONRY") (62 . 7) (370 . 13) (100 . "AcDbLine") (10 3076.9230769231
1447.963800905 0.0) (11 3058.0695022624 1447.963800905 0.0))
((0 . "LINE") (100 . "AcDbEntity") (8 . "MASONRY") (62 . 7) (370 . 13) (100 . "AcDbLine") (10 3069.381719457
1493.2126696833 0.0) (11 3076.9230769231 1493.2126696833 0.0))
((0 . "LINE") (100 . "AcDbEntity") (8 . "MASONRY") (62 . 7) (370 . 13) (100 . "AcDbLine") (10 3084.4647850679
2337.8584502262 0.0) (11 3084.4647850679 2319.0045248869 0.0))
((0 . "LINE") (100 . "AcDbEntity") (8 . "MASONRY") (62 . 7) (370 . 13) (100 . "AcDbLine") (10 3076.9230769231
1168.9295701357 0.0) (11 3122.1719457014 1168.9295701357 0.0))
((0 . "LINE") (100 . "AcDbEntity") (8 . "MASONRY") (62 . 7) (370 . 13) (100 . "AcDbLine") (10 3092.0058031674
2462.2928393665 0.0) (11 3092.0058031674 2473.6050565611 0.0))
((0 . "LINE") (100 . "AcDbEntity") (8 . "MASONRY") (62 . 7) (370 . 13) (100 . "AcDbLine") (10 3088.2352941176
1500.7550678733 0.0) (11 3303.1674208145 1500.7550678733 0.0))
((0 . "LINE") (100 . "AcDbEntity") (8 . "MASONRY") (62 . 7) (370 . 13) (100 . "AcDbLine") (10 3088.2352941176
1025.6419457014 0.0) (11 3095.7766515837 1025.6419457014 0.0))
((0 . "LINE") (100 . "AcDbEntity") (8 . "MASONRY") (62 . 7) (370 . 13) (100 . "AcDbLine") (10 3099.5475113122
1542.2313574661 0.0) (11 3099.5475113122 1557.3161538462 0.0))
((0 . "LINE") (100 . "AcDbEntity") (8 . "MASONRY") (62 . 7) (370 . 13) (100 . "AcDbLine") (10 3095.7766515837
984.1628959276 0.0) (11 3095.7766515837 1025.6419457014 0.0))
((0 . "LINE") (100 . "AcDbEntity") (8 . "MASONRY") (62 . 7) (370 . 13) (100 . "AcDbLine") (10 3246.6063348416
1025.6419457014 0.0) (11 3095.7766515837 1025.6419457014 0.0))
((0 . "LINE") (100 . "AcDbEntity") (8 . "MASONRY") (62 . 7) (370 . 13) (100 . "AcDbLine") (10 3095.7766515837
984.1628959276 0.0) (11 3122.1719457014 984.1628959276 0.0))
((0 . "LINE") (100 . "AcDbEntity") (8 . "MASONRY") (62 . 7) (370 . 13) (100 . "AcDbLine") (10 3103.3953506787
893.665158371 0.0) (11 3103.3953506787 850.8300791855 0.0))
((0 . "LINE") (100 . "AcDbEntity") (8 . "MASONRY") (62 . 7) (370 . 13) (100 . "AcDbLine") (10 3103.3953506787
850.8300791855 0.0) (11 3174.9621719457 850.8300791855 0.0))
((0 . "LINE") (100 . "AcDbEntity") (8 . "MASONRY") (62 . 7) (370 . 13) (100 . "AcDbLine") (10 3193.8161085973
718.3257918552 0.0) (11 3142.7015723982 718.3257918552 0.0))
((0 . "LINE") (100 . "AcDbEntity") (8 . "MASONRY") (62 . 7) (370 . 13) (100 . "AcDbLine") (10 3103.3183710407
2897.8125113122 0.0) (11 3227.752760181 2897.8125113122 0.0))
((0 . "LINE") (100 . "AcDbEntity") (8 . "MASONRY") (62 . 7) (370 . 13) (100 . "AcDbLine") (10 3107.0888687783
923.8319909502 0.0) (11 3435.1431674208 923.8319909502 0.0))
((0 . "LINE") (100 . "AcDbEntity") (8 . "MASONRY") (62 . 7) (370 . 13) (100 . "AcDbLine") (10 3120.2863461538
2820.5125904977 0.0) (11 3120.2863461538 2794.1176470588 0.0))
((0 . "LINE") (100 . "AcDbEntity") (8 . "MASONRY") (62 . 7) (370 . 13) (100 . "AcDbLine") (10 3120.2863461538
2820.5125904977 0.0) (11 3291.8552036199 2820.5125904977 0.0))
((0 . "LINE") (100 . "AcDbEntity") (8 . "MASONRY") (62 . 7) (370 . 13) (100 . "AcDbLine") (10 3306.938280543
2007.9185520362 0.0) (11 3125.9428054299 2007.9185520362 0.0))
((0 . "LINE") (100 . "AcDbEntity") (8 . "MASONRY") (62 . 7) (370 . 13) (100 . "AcDbLine") (10 3125.9428054299
1889.1402714932 0.0) (11 3163.6499547511 1889.1402714932 0.0))
((0 . "LINE") (100 . "AcDbEntity") (8 . "MASONRY") (62 . 7) (370 . 13) (100 . "AcDbLine") (10 3131.5985633484
1843.8914027149 0.0) (11 3131.5985633484 1858.9741289593 0.0))
((0 . "LINE") (100 . "AcDbEntity") (8 . "MASONRY") (62 . 7) (370 . 13) (100 . "AcDbLine") (10 3133.4841628959
2251.1312217195 0.0) (11 3159.8794570136 2251.1312217195 0.0))
((0 . "LINE") (100 . "AcDbEntity") (8 . "MASONRY") (62 . 7) (370 . 13) (100 . "AcDbLine") (10 3159.8794570136
2251.1312217195 0.0) (11 3182.5038914027 2251.1312217195 0.0))
((0 . "LINE") (100 . "AcDbEntity") (8 . "MASONRY") (62 . 7) (370 . 13) (100 . "AcDbLine") (10 3131.5985633484
1858.9741289593 0.0) (11 3167.4208144796 1858.9741289593 0.0))
((0 . "LINE") (100 . "AcDbEntity") (8 . "MASONRY") (62 . 7) (370 . 13) (100 . "AcDbLine") (10 3141.025520362
1670.4383257919 0.0) (11 3141.025520362 1704.3749773756 0.0))
((0 . "LINE") (100 . "AcDbEntity") (8 . "MASONRY") (62 . 7) (370 . 13) (100 . "AcDbLine") (10 3141.025520362
1670.4383257919 0.0) (11 3306.938280543 1670.4383257919 0.0))
((0 . "LINE") (100 . "AcDbEntity") (8 . "MASONRY") (62 . 7) (370 . 13) (100 . "AcDbLine") (10 3433.257918552
1265.0088461538 0.0) (11 3288.0843438914 1265.0088461538 0.0))
((0 . "LINE") (100 . "AcDbEntity") (8 . "MASONRY") (62 . 7) (370 . 13) (100 . "AcDbLine") (10 3288.0843438914
1265.0088461538 0.0) (11 3146.681979638 1265.0088461538 0.0))
((0 . "LINE") (100 . "AcDbEntity") (8 . "MASONRY") (62 . 7) (370 . 13) (100 . "AcDbLine") (10 3146.681979638
1293.3625791855 0.0) (11 3146.681979638 1265.0088461538 0.0))
((0 . "LINE") (100 . "AcDbEntity") (8 . "MASONRY") (62 . 7) (370 . 13) (100 . "AcDbLine") (10 3148.567239819
2450.9806221719 0.0) (11 3148.567239819 2398.1900452489 0.0))
((0 . "LINE") (100 . "AcDbEntity") (8 . "MASONRY") (62 . 7) (370 . 13) (100 . "AcDbLine") (10 3148.567239819
991.7039140271 0.0) (11 3589.1412895928 991.7039140271 0.0))
((0 . "LINE") (100 . "AcDbEntity") (8 . "MASONRY") (62 . 7) (370 . 13) (100 . "AcDbLine") (10 3152.3377375566
1180.0940271493 0.0) (11 3216.517861991 1180.0940271493 0.0))
((0 . "LINE") (100 . "AcDbEntity") (8 . "MASONRY") (62 . 7) (370 . 13) (100 . "AcDbLine") (10 3180.6186312217
2130.467341629 0.0) (11 3180.6186312217 2156.8629751131 0.0))
((0 . "LINE") (100 . "AcDbEntity") (8 . "MASONRY") (62 . 7) (370 . 13) (100 . "AcDbLine") (10 3180.6186312217
2156.8629751131 0.0) (11 3291.8552036199 2156.8629751131 0.0))
((0 . "LINE") (100 . "AcDbEntity") (8 . "MASONRY") (62 . 7) (370 . 13) (100 . "AcDbLine") (10 3207.0135746606
3193.8157579186 0.0) (11 3197.5866063348 3193.8157579186 0.0))
((0 . "LINE") (100 . "AcDbEntity") (8 . "MASONRY") (62 . 7) (370 . 13) (100 . "AcDbLine") (10 3201.3574660633
1864.7048076923 0.0) (11 3220.211040724 1864.7048076923 0.0))
((0 . "LINE") (100 . "AcDbEntity") (8 . "MASONRY") (62 . 7) (370 . 13) (100 . "AcDbLine") (10 3220.211040724
1864.7048076923 0.0) (11 3452.1118438914 1864.7048076923 0.0))
((0 . "LINE") (100 . "AcDbEntity") (8 . "MASONRY") (62 . 7) (370 . 13) (100 . "AcDbLine") (10 3216.4405429864
3193.8157579186 0.0) (11 3207.0135746606 3193.8157579186 0.0))
((0 . "LINE") (100 . "AcDbEntity") (8 . "MASONRY") (62 . 7) (370 . 13) (100 . "AcDbLine") (10 3207.0135746606
3193.8157579186 0.0) (11 3207.0135746606 3231.5236085973 0.0))
((0 . "LINE") (100 . "AcDbEntity") (8 . "MASONRY") (62 . 7) (370 . 13) (100 . "AcDbLine") (10 3229.6380090498
3412.5190837104 0.0) (11 3208.8988235294 3412.5190837104 0.0))
((0 . "LINE") (100 . "AcDbEntity") (8 . "MASONRY") (62 . 7) (370 . 13) (100 . "AcDbLine") (10 3227.752760181
1134.995678733 0.0) (11 3216.517861991 1134.995678733 0.0))
((0 . "LINE") (100 . "AcDbEntity") (8 . "MASONRY") (62 . 7) (370 . 13) (100 . "AcDbLine") (10 3216.517861991
1134.995678733 0.0) (11 3216.517861991 1180.0940271493 0.0))
((0 . "LINE") (100 . "AcDbEntity") (8 . "MASONRY") (62 . 7) (370 . 13) (100 . "AcDbLine") (10 3433.257918552
1180.0940271493 0.0) (11 3216.517861991 1180.0940271493 0.0))
((0 . "LINE") (100 . "AcDbEntity") (8 . "MASONRY") (62 . 7) (370 . 13) (100 . "AcDbLine") (10 3220.211040724
2754.5248868778 0.0) (11 3220.211040724 2733.7860520362 0.0))
((0 . "LINE") (100 . "AcDbEntity") (8 . "MASONRY") (62 . 7) (370 . 13) (100 . "AcDbLine") (10 3220.211040724
2754.5248868778 0.0) (11 3340.874581448 2754.5248868778 0.0))
((0 . "LINE") (100 . "AcDbEntity") (8 . "MASONRY") (62 . 7) (370 . 13) (100 . "AcDbLine") (10 3340.874581448
2754.5248868778 0.0) (11 3352.1871493213 2754.5248868778 0.0))
((0 . "LINE") (100 . "AcDbEntity") (8 . "MASONRY") (62 . 7) (370 . 13) (100 . "AcDbLine") (10 3223.9819004525
2202.1118438914 0.0) (11 3548.2653393665 2202.1118438914 0.0))
((0 . "LINE") (100 . "AcDbEntity") (8 . "MASONRY") (62 . 7) (370 . 13) (100 . "AcDbLine") (10 3229.6380090498
3329.5623642534 0.0) (11 3229.6380090498 3263.500780543 0.0))
((0 . "LINE") (100 . "AcDbEntity") (8 . "MASONRY") (62 . 7) (370 . 13) (100 . "AcDbLine") (10 3229.6380090498
3376.6968325792 0.0) (11 3229.6380090498 3329.5623642534 0.0))
((0 . "LINE") (100 . "AcDbEntity") (8 . "MASONRY") (62 . 7) (370 . 13) (100 . "AcDbLine") (10 3344.6454298643
3263.500780543 0.0) (11 3229.6380090498 3263.500780543 0.0))
((0 . "LINE") (100 . "AcDbEntity") (8 . "MASONRY") (62 . 7) (370 . 13) (100 . "AcDbLine") (10 3227.752760181
2249.2463122172 0.0) (11 3235.2941176471 2249.2463122172 0.0))
((0 . "LINE") (100 . "AcDbEntity") (8 . "MASONRY") (62 . 7) (370 . 13) (100 . "AcDbLine") (10 3229.6380090498
3412.5190837104 0.0) (11 3265.4599095023 3412.5190837104 0.0))
((0 . "LINE") (100 . "AcDbEntity") (8 . "MASONRY") (62 . 7) (370 . 13) (100 . "AcDbLine") (10 3229.6380090498
3412.5190837104 0.0) (11 3229.6380090498 3376.6968325792 0.0))
((0 . "LINE") (100 . "AcDbEntity") (8 . "MASONRY") (62 . 7) (370 . 13) (100 . "AcDbLine") (10 3288.0843438914
3376.6968325792 0.0) (11 3229.6380090498 3376.6968325792 0.0))
((0 . "LINE") (100 . "AcDbEntity") (8 . "MASONRY") (62 . 7) (370 . 13) (100 . "AcDbLine") (10 3235.2941176471
861.1100791855 0.0) (11 3235.2941176471 874.8105429864 0.0))
((0 . "LINE") (100 . "AcDbEntity") (8 . "MASONRY") (62 . 7) (370 . 13) (100 . "AcDbLine") (10 3246.9052941176
861.1100791855 0.0) (11 3235.2941176471 861.1100791855 0.0))
((0 . "LINE") (100 . "AcDbEntity") (8 . "MASONRY") (62 . 7) (370 . 13) (100 . "AcDbLine") (10 3235.2941176471
812.996561086 0.0) (11 3235.2941176471 861.1100791855 0.0))
((0 . "LINE") (100 . "AcDbEntity") (8 . "MASONRY") (62 . 7) (370 . 13) (100 . "AcDbLine") (10 3254.1476923077
3190.0452488688 0.0) (11 3295.6260633484 3190.0452488688 0.0))
((0 . "LINE") (100 . "AcDbEntity") (8 . "MASONRY") (62 . 7) (370 . 13) (100 . "AcDbLine") (10 3259.8041515837
2620.6638800905 0.0) (11 3254.1476923077 2620.6638800905 0.0))
((0 . "LINE") (100 . "AcDbEntity") (8 . "MASONRY") (62 . 7) (370 . 13) (100 . "AcDbLine") (10 3259.8041515837
2620.6638800905 0.0) (11 3259.8041515837 2576.6191402715 0.0))
((0 . "LINE") (100 . "AcDbEntity") (8 . "MASONRY") (62 . 7) (370 . 13) (100 . "AcDbLine") (10 3344.6454298643
2576.6191402715 0.0) (11 3259.8041515837 2576.6191402715 0.0))
((0 . "LINE") (100 . "AcDbEntity") (8 . "MASONRY") (62 . 7) (370 . 13) (100 . "AcDbLine") (10 3259.8041515837
2620.6638800905 0.0) (11 3344.6454298643 2620.6638800905 0.0))
((0 . "LINE") (100 . "AcDbEntity") (8 . "MASONRY") (62 . 7) (370 . 13) (100 . "AcDbLine") (10 3276.7721266968
2100.3018891403 0.0) (11 3269.2307692308 2100.3018891403 0.0))
((0 . "LINE") (100 . "AcDbEntity") (8 . "MASONRY") (62 . 7) (370 . 13) (100 . "AcDbLine") (10 3348.4162895928
3414.4046832579 0.0) (11 3280.5429864253 3414.4046832579 0.0))
((0 . "LINE") (100 . "AcDbEntity") (8 . "MASONRY") (62 . 7) (370 . 13) (100 . "AcDbLine") (10 3280.5429864253
2894.0426923077 0.0) (11 3344.6454298643 2894.0426923077 0.0))
((0 . "LINE") (100 . "AcDbEntity") (8 . "MASONRY") (62 . 7) (370 . 13) (100 . "AcDbLine") (10 3310.7087782805
1131.221719457 0.0) (11 3280.5429864253 1131.221719457 0.0))
((0 . "LINE") (100 . "AcDbEntity") (8 . "MASONRY") (62 . 7) (370 . 13) (100 . "AcDbLine") (10 3284.3138461538
2260.483959276 0.0) (11 3431.3726696833 2260.483959276 0.0))
((0 . "LINE") (100 . "AcDbEntity") (8 . "MASONRY") (62 . 7) (370 . 13) (100 . "AcDbLine") (10 3340.8749321267
2806.5566628959 0.0) (11 3291.8552036199 2806.5566628959 0.0))
((0 . "LINE") (100 . "AcDbEntity") (8 . "MASONRY") (62 . 7) (370 . 13) (100 . "AcDbLine") (10 3291.8552036199
2806.5566628959 0.0) (11 3291.8552036199 2820.5125904977 0.0))
((0 . "LINE") (100 . "AcDbEntity") (8 . "MASONRY") (62 . 7) (370 . 13) (100 . "AcDbLine") (10 3291.8552036199
2843.1370248869 0.0) (11 3291.8552036199 2820.5125904977 0.0))
((0 . "LINE") (100 . "AcDbEntity") (8 . "MASONRY") (62 . 7) (370 . 13) (100 . "AcDbLine") (10 3687.7828054299
2100.3018891403 0.0) (11 3288.0843438914 2100.3018891403 0.0))
((0 . "LINE") (100 . "AcDbEntity") (8 . "MASONRY") (62 . 7) (370 . 13) (100 . "AcDbLine") (10 3297.5113122172
2051.281821267 0.0) (11 3297.5113122172 2062.5940384615 0.0))
((0 . "LINE") (100 . "AcDbEntity") (8 . "MASONRY") (62 . 7) (370 . 13) (100 . "AcDbLine") (10 3303.1674208145
1500.7550678733 0.0) (11 3303.1674208145 1561.0859728507 0.0))
((0 . "LINE") (100 . "AcDbEntity") (8 . "MASONRY") (62 . 7) (370 . 13) (100 . "AcDbLine") (10 3578.4314932127
1500.7550678733 0.0) (11 3303.1674208145 1500.7550678733 0.0))
((0 . "LINE") (100 . "AcDbEntity") (8 . "MASONRY") (62 . 7) (370 . 13) (100 . "AcDbLine") (10 3306.938280543
1598.7924434389 0.0) (11 3306.938280543 1606.334841629 0.0))
((0 . "LINE") (100 . "AcDbEntity") (8 . "MASONRY") (62 . 7) (370 . 13) (100 . "AcDbLine") (10 3306.938280543
1606.334841629 0.0) (11 3306.938280543 1625.1121266968 0.0))
((0 . "LINE") (100 . "AcDbEntity") (8 . "MASONRY") (62 . 7) (370 . 13) (100 . "AcDbLine") (10 3306.938280543
1625.1121266968 0.0) (11 3306.938280543 1670.4383257919 0.0))
((0 . "LINE") (100 . "AcDbEntity") (8 . "MASONRY") (62 . 7) (370 . 13) (100 . "AcDbLine") (10 3306.938280543
1670.4383257919 0.0) (11 3325.7918552036 1670.4383257919 0.0))
((0 . "LINE") (100 . "AcDbEntity") (8 . "MASONRY") (62 . 7) (370 . 13) (100 . "AcDbLine") (10 3310.7087782805
1131.221719457 0.0) (11 3310.7087782805 1116.1396832579 0.0))
((0 . "LINE") (100 . "AcDbEntity") (8 . "MASONRY") (62 . 7) (370 . 13) (100 . "AcDbLine") (10 3310.7087782805
1153.8461538462 0.0) (11 3310.7087782805 1131.221719457 0.0))
((0 . "LINE") (100 . "AcDbEntity") (8 . "MASONRY") (62 . 7) (370 . 13) (100 . "AcDbLine") (10 3310.7091289593
889.8953393665 0.0) (11 3310.7091289593 882.3529411765 0.0))
((0 . "LINE") (100 . "AcDbEntity") (8 . "MASONRY") (62 . 7) (370 . 13) (100 . "AcDbLine") (10 3310.7087782805
3110.8597285068 0.0) (11 3348.4162895928 3110.8597285068 0.0))
((0 . "LINE") (100 . "AcDbEntity") (8 . "MASONRY") (62 . 7) (370 . 13) (100 . "AcDbLine") (10 3582.2019909502
1602.7120927602 0.0) (11 3582.2019909502 1625.1121266968 0.0))
((0 . "LINE") (100 . "AcDbEntity") (8 . "MASONRY") (62 . 7) (370 . 13) (100 . "AcDbLine") (10 3582.2019909502
1625.1121266968 0.0) (11 3306.938280543 1625.1121266968 0.0))
((0 . "LINE") (100 . "AcDbEntity") (8 . "MASONRY") (62 . 7) (370 . 13) (100 . "AcDbLine") (10 3320.1357466063
1297.135158371 0.0) (11 3320.1357466063 1332.956719457 0.0))
((0 . "LINE") (100 . "AcDbEntity") (8 . "MASONRY") (62 . 7) (370 . 13) (100 . "AcDbLine") (10 3337.1040723982
3378.5824321267 0.0) (11 3322.0209954751 3378.5824321267 0.0))
((0 . "LINE") (100 . "AcDbEntity") (8 . "MASONRY") (62 . 7) (370 . 13) (100 . "AcDbLine") (10 3593.5142081448
1332.956719457 0.0) (11 3320.1357466063 1332.956719457 0.0))
((0 . "LINE") (100 . "AcDbEntity") (8 . "MASONRY") (62 . 7) (370 . 13) (100 . "AcDbLine") (10 3322.0209954751
1217.949638009 0.0) (11 3337.1040723982 1217.949638009 0.0))
((0 . "LINE") (100 . "AcDbEntity") (8 . "MASONRY") (62 . 7) (370 . 13) (100 . "AcDbLine") (10 3352.1871493213
2658.371040724 0.0) (11 3329.5627149321 2658.371040724 0.0))
((0 . "LINE") (100 . "AcDbEntity") (8 . "MASONRY") (62 . 7) (370 . 13) (100 . "AcDbLine") (10 3359.7285067873
1442.3076923077 0.0) (11 3329.5627149321 1442.3076923077 0.0))
((0 . "LINE") (100 . "AcDbEntity") (8 . "MASONRY") (62 . 7) (370 . 13) (100 . "AcDbLine") (10 3333.3332126697
1817.4971493213 0.0) (11 3567.1192760181 1817.4971493213 0.0))
((0 . "LINE") (100 . "AcDbEntity") (8 . "MASONRY") (62 . 7) (370 . 13) (100 . "AcDbLine") (10 3337.1040723982
2011.6897511312 0.0) (11 3408.7482352941 2011.6897511312 0.0))
((0 . "LINE") (100 . "AcDbEntity") (8 . "MASONRY") (62 . 7) (370 . 13) (100 . "AcDbLine") (10 3348.4162895928
3178.7330316742 0.0) (11 3348.4162895928 3193.8157579186 0.0))
((0 . "LINE") (100 . "AcDbEntity") (8 . "MASONRY") (62 . 7) (370 . 13) (100 . "AcDbLine") (10 3350.3018891403
2843.1370248869 0.0) (11 3350.3018891403 2854.4492420814 0.0))
((0 . "LINE") (100 . "AcDbEntity") (8 . "MASONRY") (62 . 7) (370 . 13) (100 . "AcDbLine") (10 3348.4162895928
1738.3116289593 0.0) (11 3363.4993665158 1738.3116289593 0.0))
((0 . "LINE") (100 . "AcDbEntity") (8 . "MASONRY") (62 . 7) (370 . 13) (100 . "AcDbLine") (10 3348.4162895928
1670.4383257919 0.0) (11 3378.582081448 1670.4383257919 0.0))
((0 . "LINE") (100 . "AcDbEntity") (8 . "MASONRY") (62 . 7) (370 . 13) (100 . "AcDbLine") (10 3465.309321267
823.9069457014 0.0) (11 3348.4162895928 823.9069457014 0.0))
((0 . "LINE") (100 . "AcDbEntity") (8 . "MASONRY") (62 . 7) (370 . 13) (100 . "AcDbLine") (10 3352.1871493213
3152.3380882353 0.0) (11 3352.1871493213 3159.8791063348 0.0))
((0 . "LINE") (100 . "AcDbEntity") (8 . "MASONRY") (62 . 7) (370 . 13) (100 . "AcDbLine") (10 3371.0407239819
1451.5803393665 0.0) (11 3578.4314932127 1451.5803393665 0.0))
((0 . "LINE") (100 . "AcDbEntity") (8 . "MASONRY") (62 . 7) (370 . 13) (100 . "AcDbLine") (10 3393.665158371
1674.2081447964 0.0) (11 3412.5187330317 1674.2081447964 0.0))
((0 . "LINE") (100 . "AcDbEntity") (8 . "MASONRY") (62 . 7) (370 . 13) (100 . "AcDbLine") (10 3563.0812104072
785.4264932127 0.0) (11 3563.0812104072 814.4727375566 0.0))
((0 . "LINE") (100 . "AcDbEntity") (8 . "MASONRY") (62 . 7) (370 . 13) (100 . "AcDbLine") (10 3563.0812104072
814.4727375566 0.0) (11 3555.8067081448 814.4727375566 0.0))
((0 . "LINE") (100 . "AcDbEntity") (8 . "MASONRY") (62 . 7) (370 . 13) (100 . "AcDbLine") (10 3555.8067081448
814.4727375566 0.0) (11 3444.3450565611 814.4727375566 0.0))
((0 . "LINE") (100 . "AcDbEntity") (8 . "MASONRY") (62 . 7) (370 . 13) (100 . "AcDbLine") (10 3444.3450565611
814.4727375566 0.0) (11 3444.3450565611 610.7817081448 0.0))
((0 . "LINE") (100 . "AcDbEntity") (8 . "MASONRY") (62 . 7) (370 . 13) (100 . "AcDbLine") (10 3555.8070588235
1738.163178733 0.0) (11 3435.1431674208 1738.163178733 0.0))
((0 . "LINE") (100 . "AcDbEntity") (8 . "MASONRY") (62 . 7) (370 . 13) (100 . "AcDbLine") (10 3435.1431674208
1738.163178733 0.0) (11 3416.8916628959 1738.163178733 0.0))
((0 . "LINE") (100 . "AcDbEntity") (8 . "MASONRY") (62 . 7) (370 . 13) (100 . "AcDbLine") (10 3416.8916628959
1738.163178733 0.0) (11 3416.8916628959 1711.9146153846 0.0))
((0 . "LINE") (100 . "AcDbEntity") (8 . "MASONRY") (62 . 7) (370 . 13) (100 . "AcDbLine") (10 3423.8309502262
889.8953393665 0.0) (11 3435.1431674208 889.8953393665 0.0))
((0 . "LINE") (100 . "AcDbEntity") (8 . "MASONRY") (62 . 7) (370 . 13) (100 . "AcDbLine") (10 3431.3726696833
2239.8190045249 0.0) (11 3431.3726696833 2260.483959276 0.0))
((0 . "LINE") (100 . "AcDbEntity") (8 . "MASONRY") (62 . 7) (370 . 13) (100 . "AcDbLine") (10 3616.1386425339
2260.483959276 0.0) (11 3544.494841629 2260.483959276 0.0))
((0 . "LINE") (100 . "AcDbEntity") (8 . "MASONRY") (62 . 7) (370 . 13) (100 . "AcDbLine") (10 3544.494841629
2260.483959276 0.0) (11 3431.3726696833 2260.483959276 0.0))
((0 . "LINE") (100 . "AcDbEntity") (8 . "MASONRY") (62 . 7) (370 . 13) (100 . "AcDbLine") (10 3653.9973642534
1199.0950226244 0.0) (11 3653.9973642534 1180.0940271493 0.0))
((0 . "LINE") (100 . "AcDbEntity") (8 . "MASONRY") (62 . 7) (370 . 13) (100 . "AcDbLine") (10 3653.9973642534
1180.0940271493 0.0) (11 3433.257918552 1180.0940271493 0.0))
((0 . "LINE") (100 . "AcDbEntity") (8 . "MASONRY") (62 . 7) (370 . 13) (100 . "AcDbLine") (10 3433.257918552
1265.0088461538 0.0) (11 3433.257918552 1180.0940271493 0.0))
((0 . "LINE") (100 . "AcDbEntity") (8 . "MASONRY") (62 . 7) (370 . 13) (100 . "AcDbLine") (10 3433.257918552
1265.0088461538 0.0) (11 3618.0239027149 1265.0088461538 0.0))
((0 . "LINE") (100 . "AcDbEntity") (8 . "MASONRY") (62 . 7) (370 . 13) (100 . "AcDbLine") (10 3435.1431674208
942.6838461538 0.0) (11 3435.1431674208 923.8319909502 0.0))
((0 . "LINE") (100 . "AcDbEntity") (8 . "MASONRY") (62 . 7) (370 . 13) (100 . "AcDbLine") (10 3435.1431674208
923.8319909502 0.0) (11 3435.1431674208 889.8953393665 0.0))
((0 . "LINE") (100 . "AcDbEntity") (8 . "MASONRY") (62 . 7) (370 . 13) (100 . "AcDbLine") (10 3450.2262443439
889.8953393665 0.0) (11 3435.1431674208 889.8953393665 0.0))
((0 . "LINE") (100 . "AcDbEntity") (8 . "MASONRY") (62 . 7) (370 . 13) (100 . "AcDbLine") (10 3452.1118438914
1864.7048076923 0.0) (11 3452.1118438914 1896.681979638 0.0))
((0 . "LINE") (100 . "AcDbEntity") (8 . "MASONRY") (62 . 7) (370 . 13) (100 . "AcDbLine") (10 3608.5972850679
1864.7048076923 0.0) (11 3452.1118438914 1864.7048076923 0.0))
((0 . "LINE") (100 . "AcDbEntity") (8 . "MASONRY") (62 . 7) (370 . 13) (100 . "AcDbLine") (10 3470.9654298643
3435.1435180995 0.0) (11 3470.9654298643 3472.850678733 0.0))
((0 . "LINE") (100 . "AcDbEntity") (8 . "MASONRY") (62 . 7) (370 . 13) (100 . "AcDbLine") (10 3704.7511312217
3472.850678733 0.0) (11 3470.9654298643 3472.850678733 0.0))
((0 . "LINE") (100 . "AcDbEntity") (8 . "MASONRY") (62 . 7) (370 . 13) (100 . "AcDbLine") (10 3472.850678733
1404.6771719457 0.0) (11 3736.8021832579 1404.6771719457 0.0))
((0 . "LINE") (100 . "AcDbEntity") (8 . "MASONRY") (62 . 7) (370 . 13) (100 . "AcDbLine") (10 3736.8021832579
1404.6771719457 0.0) (11 3736.8021832579 1432.8817647059 0.0))
((0 . "LINE") (100 . "AcDbEntity") (8 . "MASONRY") (62 . 7) (370 . 13) (100 . "AcDbLine") (10 3499.2459728507
2492.4582918552 0.0) (11 3484.1628959276 2492.4582918552 0.0))
((0 . "LINE") (100 . "AcDbEntity") (8 . "MASONRY") (62 . 7) (370 . 13) (100 . "AcDbLine") (10 3535.7994004525
585.8256447964 0.0) (11 3619.9095022624 585.8256447964 0.0))
((0 . "LINE") (100 . "AcDbEntity") (8 . "MASONRY") (62 . 7) (370 . 13) (100 . "AcDbLine") (10 3619.9095022624
585.8256447964 0.0) (11 3673.9145701357 585.8256447964 0.0))
((0 . "LINE") (100 . "AcDbEntity") (8 . "MASONRY") (62 . 7) (370 . 13) (100 . "AcDbLine") (10 3499.2459728507
2492.4582918552 0.0) (11 3499.2459728507 2473.6050565611 0.0))
((0 . "LINE") (100 . "AcDbEntity") (8 . "MASONRY") (62 . 7) (370 . 13) (100 . "AcDbLine") (10 3499.2459728507
2492.4582918552 0.0) (11 3540.7239819005 2492.4582918552 0.0))
((0 . "LINE") (100 . "AcDbEntity") (8 . "MASONRY") (62 . 7) (370 . 13) (100 . "AcDbLine") (10 3535.0678733032
897.4349773756 0.0) (11 3499.2459728507 897.4349773756 0.0))
((0 . "LINE") (100 . "AcDbEntity") (8 . "MASONRY") (62 . 7) (370 . 13) (100 . "AcDbLine") (10 3503.0164705882
2013.5746606335 0.0) (11 3578.4314932127 2013.5746606335 0.0))
((0 . "LINE") (100 . "AcDbEntity") (8 . "MASONRY") (62 . 7) (370 . 13) (100 . "AcDbLine") (10 3589.1412895928
991.7039140271 0.0) (11 3589.1412895928 1036.9541628959 0.0))
((0 . "LINE") (100 . "AcDbEntity") (8 . "MASONRY") (62 . 7) (370 . 13) (100 . "AcDbLine") (10 3589.1412895928
1036.9541628959 0.0) (11 3570.8897737557 1036.9541628959 0.0))
((0 . "LINE") (100 . "AcDbEntity") (8 . "MASONRY") (62 . 7) (370 . 13) (100 . "AcDbLine") (10 3570.8897737557
1036.9541628959 0.0) (11 3506.7873303167 1036.9541628959 0.0))
((0 . "LINE") (100 . "AcDbEntity") (8 . "MASONRY") (62 . 7) (370 . 13) (100 . "AcDbLine") (10 3606.7085746606
2320.8894343891 0.0) (11 3523.7556561086 2320.8894343891 0.0))
((0 . "LINE") (100 . "AcDbEntity") (8 . "MASONRY") (62 . 7) (370 . 13) (100 . "AcDbLine") (10 3523.7556561086
2320.8894343891 0.0) (11 3523.7556561086 2296.3800904977 0.0))
((0 . "LINE") (100 . "AcDbEntity") (8 . "MASONRY") (62 . 7) (370 . 13) (100 . "AcDbLine") (10 3606.7085746606
2320.8894343891 0.0) (11 3606.7085746606 2378.1319909502 0.0))
((0 . "LINE") (100 . "AcDbEntity") (8 . "MASONRY") (62 . 7) (370 . 13) (100 . "AcDbLine") (10 3606.7085746606
2378.1319909502 0.0) (11 3518.0995475113 2378.1319909502 0.0))
((0 . "LINE") (100 . "AcDbEntity") (8 . "MASONRY") (62 . 7) (370 . 13) (100 . "AcDbLine") (10 3518.0995475113
2349.1706674208 0.0) (11 3518.0995475113 2378.1319909502 0.0))
((0 . "LINE") (100 . "AcDbEntity") (8 . "MASONRY") (62 . 7) (370 . 13) (100 . "AcDbLine") (10 3585.9728506787
881.07010181 0.0) (11 3535.0678733032 881.07010181 0.0))
((0 . "LINE") (100 . "AcDbEntity") (8 . "MASONRY") (62 . 7) (370 . 13) (100 . "AcDbLine") (10 3535.0678733032
881.07010181 0.0) (11 3535.0678733032 897.4349773756 0.0))
((0 . "LINE") (100 . "AcDbEntity") (8 . "MASONRY") (62 . 7) (370 . 13) (100 . "AcDbLine") (10 3672.6997285068
897.4349773756 0.0) (11 3535.0678733032 897.4349773756 0.0))
((0 . "LINE") (100 . "AcDbEntity") (8 . "MASONRY") (62 . 7) (370 . 13) (100 . "AcDbLine") (10 4096.9082239819
2198.3406447964 0.0) (11 3563.3484162896 2198.3406447964 0.0))
((0 . "LINE") (100 . "AcDbEntity") (8 . "MASONRY") (62 . 7) (370 . 13) (100 . "AcDbLine") (10 3578.4314932127
1500.7550678733 0.0) (11 3578.4314932127 1451.5803393665 0.0))
((0 . "LINE") (100 . "AcDbEntity") (8 . "MASONRY") (62 . 7) (370 . 13) (100 . "AcDbLine") (10 3578.4314932127
1500.7550678733 0.0) (11 3578.4314932127 1515.8371040724 0.0))
((0 . "LINE") (100 . "AcDbEntity") (8 . "MASONRY") (62 . 7) (370 . 13) (100 . "AcDbLine") (10 3595.3994683258
1738.3116289593 0.0) (11 3574.6606334842 1738.3116289593 0.0))
((0 . "LINE") (100 . "AcDbEntity") (8 . "MASONRY") (62 . 7) (370 . 13) (100 . "AcDbLine") (10 3800.9049773756
1817.4971493213 0.0) (11 3782.0514027149 1817.4971493213 0.0))
((0 . "LINE") (100 . "AcDbEntity") (8 . "MASONRY") (62 . 7) (370 . 13) (100 . "AcDbLine") (10 3782.0514027149
1817.4971493213 0.0) (11 3578.4314932127 1817.4971493213 0.0))
((0 . "LINE") (100 . "AcDbEntity") (8 . "MASONRY") (62 . 7) (370 . 13) (100 . "AcDbLine") (10 3582.2019909502
1557.3161538462 0.0) (11 3582.2019909502 1602.7120927602 0.0))
((0 . "LINE") (100 . "AcDbEntity") (8 . "MASONRY") (62 . 7) (370 . 13) (100 . "AcDbLine") (10 3582.2019909502
1602.7120927602 0.0) (11 3634.9925791855 1602.7120927602 0.0))
((0 . "LINE") (100 . "AcDbEntity") (8 . "MASONRY") (62 . 7) (370 . 13) (100 . "AcDbLine") (10 3634.9925791855
1602.7120927602 0.0) (11 3750 1602.7120927602 0.0))
((0 . "LINE") (100 . "AcDbEntity") (8 . "MASONRY") (62 . 7) (370 . 13) (100 . "AcDbLine") (10 3872.549479638
2511.3122171946 0.0) (11 3585.9728506787 2511.3122171946 0.0))
((0 . "LINE") (100 . "AcDbEntity") (8 . "MASONRY") (62 . 7) (370 . 13) (100 . "AcDbLine") (10 3585.9728506787
2053.1674208145 0.0) (11 3719.8338574661 2053.1674208145 0.0))
((0 . "LINE") (100 . "AcDbEntity") (8 . "MASONRY") (62 . 7) (370 . 13) (100 . "AcDbLine") (10 3578.4314932127
1451.5803393665 0.0) (11 3736.8021832579 1451.5803393665 0.0))
((0 . "LINE") (100 . "AcDbEntity") (8 . "MASONRY") (62 . 7) (370 . 13) (100 . "AcDbLine") (10 3736.8021832579
1451.5803393665 0.0) (11 3736.8021832579 1432.8817647059 0.0))
((0 . "LINE") (100 . "AcDbEntity") (8 . "MASONRY") (62 . 7) (370 . 13) (100 . "AcDbLine") (10 3597.2850678733
3412.5190837104 0.0) (11 3597.2850678733 3382.3529411765 0.0))
((0 . "LINE") (100 . "AcDbEntity") (8 . "MASONRY") (62 . 7) (370 . 13) (100 . "AcDbLine") (10 3815.9883936652
3254.1480429864 0.0) (11 3589.7437104072 3254.1480429864 0.0))
((0 . "LINE") (100 . "AcDbEntity") (8 . "MASONRY") (62 . 7) (370 . 13) (100 . "AcDbLine") (10 3589.7437104072
3050.5281334842 0.0) (11 3623.680361991 3050.5281334842 0.0))
((0 . "LINE") (100 . "AcDbEntity") (8 . "MASONRY") (62 . 7) (370 . 13) (100 . "AcDbLine") (10 3589.7437104072
2818.5496606335 0.0) (11 3619.3074321267 2818.5496606335 0.0))
((0 . "LINE") (100 . "AcDbEntity") (8 . "MASONRY") (62 . 7) (370 . 13) (100 . "AcDbLine") (10 3619.3074321267
2818.5496606335 0.0) (11 3619.3074321267 2775.2637217195 0.0))
((0 . "LINE") (100 . "AcDbEntity") (8 . "MASONRY") (62 . 7) (370 . 13) (100 . "AcDbLine") (10 3655.6544230769
2635.7466063348 0.0) (11 3655.6544230769 2600.5271153846 0.0))
((0 . "LINE") (100 . "AcDbEntity") (8 . "MASONRY") (62 . 7) (370 . 13) (100 . "AcDbLine") (10 3655.6544230769
2600.5271153846 0.0) (11 3589.7437104072 2600.5271153846 0.0))
((0 . "LINE") (100 . "AcDbEntity") (8 . "MASONRY") (62 . 7) (370 . 13) (100 . "AcDbLine") (10 3589.1412895928
991.7039140271 0.0) (11 3729.2608144796 991.7039140271 0.0))
((0 . "LINE") (100 . "AcDbEntity") (8 . "MASONRY") (62 . 7) (370 . 13) (100 . "AcDbLine") (10 3596.0018778281
509.0497737557 0.0) (11 3596.0018778281 497.7375565611 0.0))
((0 . "LINE") (100 . "AcDbEntity") (8 . "MASONRY") (62 . 7) (370 . 13) (100 . "AcDbLine") (10 3673.9145701357
497.7375565611 0.0) (11 3673.9145701357 585.8256447964 0.0))
((0 . "LINE") (100 . "AcDbEntity") (8 . "MASONRY") (62 . 7) (370 . 13) (100 . "AcDbLine") (10 3593.5142081448
3182.503540724 0.0) (11 3604.8264253394 3182.503540724 0.0))
((0 . "LINE") (100 . "AcDbEntity") (8 . "MASONRY") (62 . 7) (370 . 13) (100 . "AcDbLine") (10 3604.8264253394
3122.1719457014 0.0) (11 3604.8264253394 3182.503540724 0.0))
((0 . "LINE") (100 . "AcDbEntity") (8 . "MASONRY") (62 . 7) (370 . 13) (100 . "AcDbLine") (10 3616.1386425339
2995.8526470588 0.0) (11 3593.5142081448 2995.8526470588 0.0))
((0 . "LINE") (100 . "AcDbEntity") (8 . "MASONRY") (62 . 7) (370 . 13) (100 . "AcDbLine") (10 3593.5142081448
2635.7466063348 0.0) (11 3655.6544230769 2635.7466063348 0.0))
((0 . "LINE") (100 . "AcDbEntity") (8 . "MASONRY") (62 . 7) (370 . 13) (100 . "AcDbLine") (10 3653.8427036199
2533.9366515837 0.0) (11 3653.8427036199 2554.0741063348 0.0))
((0 . "LINE") (100 . "AcDbEntity") (8 . "MASONRY") (62 . 7) (370 . 13) (100 . "AcDbLine") (10 3653.8427036199
2554.0741063348 0.0) (11 3593.5142081448 2554.0741063348 0.0))
((0 . "LINE") (100 . "AcDbEntity") (8 . "MASONRY") (62 . 7) (370 . 13) (100 . "AcDbLine") (10 3595.3994683258
1738.3116289593 0.0) (11 3595.3994683258 1764.7058823529 0.0))
((0 . "LINE") (100 . "AcDbEntity") (8 . "MASONRY") (62 . 7) (370 . 13) (100 . "AcDbLine") (10 3981.9004524887
2894.0426923077 0.0) (11 3597.2850678733 2894.0426923077 0.0))
((0 . "LINE") (100 . "AcDbEntity") (8 . "MASONRY") (62 . 7) (370 . 13) (100 . "AcDbLine") (10 3595.3994683258
1738.3116289593 0.0) (11 3619.9095022624 1738.3116289593 0.0))
((0 . "LINE") (100 . "AcDbEntity") (8 . "MASONRY") (62 . 7) (370 . 13) (100 . "AcDbLine") (10 3970.5882352941
1934.2821266968 0.0) (11 3721.8675565611 1934.2821266968 0.0))
((0 . "LINE") (100 . "AcDbEntity") (8 . "MASONRY") (62 . 7) (370 . 13) (100 . "AcDbLine") (10 3721.8675565611
1934.2821266968 0.0) (11 3706.6363800905 1934.2821266968 0.0))
((0 . "LINE") (100 . "AcDbEntity") (8 . "MASONRY") (62 . 7) (370 . 13) (100 . "AcDbLine") (10 3706.6363800905
1934.2821266968 0.0) (11 3601.0559276018 1934.2821266968 0.0))
((0 . "LINE") (100 . "AcDbEntity") (8 . "MASONRY") (62 . 7) (370 . 13) (100 . "AcDbLine") (10 3601.0559276018
727.751719457 0.0) (11 4110.106040724 727.751719457 0.0))
((0 . "LINE") (100 . "AcDbEntity") (8 . "MASONRY") (62 . 7) (370 . 13) (100 . "AcDbLine") (10 3604.8264253394
2963.8009049774 0.0) (11 3604.8264253394 2944.946979638 0.0))
((0 . "LINE") (100 . "AcDbEntity") (8 . "MASONRY") (62 . 7) (370 . 13) (100 . "AcDbLine") (10 3606.7085746606
2320.8894343891 0.0) (11 3783.9366515837 2320.8894343891 0.0))
((0 . "LINE") (100 . "AcDbEntity") (8 . "MASONRY") (62 . 7) (370 . 13) (100 . "AcDbLine") (10 3608.5972850679
1332.956719457 0.0) (11 3619.9095022624 1332.956719457 0.0))
((0 . "LINE") (100 . "AcDbEntity") (8 . "MASONRY") (62 . 7) (370 . 13) (100 . "AcDbLine") (10 3634.9925791855
531.6742081448 0.0) (11 3608.5972850679 531.6742081448 0.0))
((0 . "LINE") (100 . "AcDbEntity") (8 . "MASONRY") (62 . 7) (370 . 13) (100 . "AcDbLine") (10 3612.3681447964
2420.814479638 0.0) (11 3612.3681447964 2458.5216402715 0.0))
((0 . "LINE") (100 . "AcDbEntity") (8 . "MASONRY") (62 . 7) (370 . 13) (100 . "AcDbLine") (10 3604.8264253394
3182.503540724 0.0) (11 3650.0752941176 3182.503540724 0.0))
((0 . "LINE") (100 . "AcDbEntity") (8 . "MASONRY") (62 . 7) (370 . 13) (100 . "AcDbLine") (10 3981.9004524887
1265.0088461538 0.0) (11 3618.0239027149 1265.0088461538 0.0))
((0 . "LINE") (100 . "AcDbEntity") (8 . "MASONRY") (62 . 7) (370 . 13) (100 . "AcDbLine") (10 3618.0239027149
1293.3625791855 0.0) (11 3618.0239027149 1265.0088461538 0.0))
((0 . "LINE") (100 . "AcDbEntity") (8 . "MASONRY") (62 . 7) (370 . 13) (100 . "AcDbLine") (10 3889.5171153846
805.1117081448 0.0) (11 3868.778280543 805.1117081448 0.0))
((0 . "LINE") (100 . "AcDbEntity") (8 . "MASONRY") (62 . 7) (370 . 13) (100 . "AcDbLine") (10 3868.778280543
805.1117081448 0.0) (11 3623.680361991 805.1117081448 0.0))
((0 . "LINE") (100 . "AcDbEntity") (8 . "MASONRY") (62 . 7) (370 . 13) (100 . "AcDbLine") (10 3631.221719457
2243.5895135747 0.0) (11 3793.363959276 2243.5895135747 0.0))
((0 . "LINE") (100 . "AcDbEntity") (8 . "MASONRY") (62 . 7) (370 . 13) (100 . "AcDbLine") (10 3638.7630769231
3416.2895927602 0.0) (11 3680.2414479638 3416.2895927602 0.0))
((0 . "LINE") (100 . "AcDbEntity") (8 . "MASONRY") (62 . 7) (370 . 13) (100 . "AcDbLine") (10 3638.7630769231
3337.1040723982 0.0) (11 3810.3315950226 3337.1040723982 0.0))
((0 . "LINE") (100 . "AcDbEntity") (8 . "MASONRY") (62 . 7) (370 . 13) (100 . "AcDbLine") (10 3758.1437782805
1739.5199095023 0.0) (11 3642.5339366516 1739.5199095023 0.0))
((0 . "LINE") (100 . "AcDbEntity") (8 . "MASONRY") (62 . 7) (370 . 13) (100 . "AcDbLine") (10 3646.3047963801
2780.920520362 0.0) (11 3748.1147511312 2780.920520362 0.0))
((0 . "LINE") (100 . "AcDbEntity") (8 . "MASONRY") (62 . 7) (370 . 13) (100 . "AcDbLine") (10 3655.6544230769
2635.7466063348 0.0) (11 3940.4227828054 2635.7466063348 0.0))
((0 . "LINE") (100 . "AcDbEntity") (8 . "MASONRY") (62 . 7) (370 . 13) (100 . "AcDbLine") (10 3657.6170135747
1157.6159728507 0.0) (11 3657.6170135747 1150.0763348416 0.0))
((0 . "LINE") (100 . "AcDbEntity") (8 . "MASONRY") (62 . 7) (370 . 13) (100 . "AcDbLine") (10 3661.3875113122
3188.1603393665 0.0) (11 4000.7536877828 3188.1603393665 0.0))
((0 . "LINE") (100 . "AcDbEntity") (8 . "MASONRY") (62 . 7) (370 . 13) (100 . "AcDbLine") (10 3725.4903167421
1336.7265384615 0.0) (11 3668.9292307692 1336.7265384615 0.0))
((0 . "LINE") (100 . "AcDbEntity") (8 . "MASONRY") (62 . 7) (370 . 13) (100 . "AcDbLine") (10 3887.6315158371
859.7285067873 0.0) (11 3684.0119457014 859.7285067873 0.0))
((0 . "LINE") (100 . "AcDbEntity") (8 . "MASONRY") (62 . 7) (370 . 13) (100 . "AcDbLine") (10 3684.0119457014
859.7285067873 0.0) (11 3668.9292307692 859.7285067873 0.0))
((0 . "LINE") (100 . "AcDbEntity") (8 . "MASONRY") (62 . 7) (370 . 13) (100 . "AcDbLine") (10 3676.4705882353
3052.3364027149 0.0) (11 3750 3052.3364027149 0.0))
((0 . "LINE") (100 . "AcDbEntity") (8 . "MASONRY") (62 . 7) (370 . 13) (100 . "AcDbLine") (10 3704.7511312217
3472.850678733 0.0) (11 3780.1661425339 3472.850678733 0.0))
((0 . "LINE") (100 . "AcDbEntity") (8 . "MASONRY") (62 . 7) (370 . 13) (100 . "AcDbLine") (10 3704.7511312217
3487.9334049774 0.0) (11 3704.7511312217 3472.850678733 0.0))
((0 . "LINE") (100 . "AcDbEntity") (8 . "MASONRY") (62 . 7) (370 . 13) (100 . "AcDbLine") (10 3710.407239819
3529.4117647059 0.0) (11 3963.0472171946 3529.4117647059 0.0))
((0 . "LINE") (100 . "AcDbEntity") (8 . "MASONRY") (62 . 7) (370 . 13) (100 . "AcDbLine") (10 3719.8338574661
1990.9502262443 0.0) (11 3719.8338574661 2053.1674208145 0.0))
((0 . "LINE") (100 . "AcDbEntity") (8 . "MASONRY") (62 . 7) (370 . 13) (100 . "AcDbLine") (10 3800.3029072398
2053.1674208145 0.0) (11 3719.8338574661 2053.1674208145 0.0))
((0 . "LINE") (100 . "AcDbEntity") (8 . "MASONRY") (62 . 7) (370 . 13) (100 . "AcDbLine") (10 3736.8025339367
585.8256447964 0.0) (11 3673.9145701357 585.8256447964 0.0))
((0 . "LINE") (100 . "AcDbEntity") (8 . "MASONRY") (62 . 7) (370 . 13) (100 . "AcDbLine") (10 3731.1464253394
1070.8908144796 0.0) (11 3731.1464253394 1099.0940271493 0.0))
((0 . "LINE") (100 . "AcDbEntity") (8 . "MASONRY") (62 . 7) (370 . 13) (100 . "AcDbLine") (10 4098.7938235294
1074.7352036199 0.0) (11 3980.0117420814 1074.7352036199 0.0))
((0 . "LINE") (100 . "AcDbEntity") (8 . "MASONRY") (62 . 7) (370 . 13) (100 . "AcDbLine") (10 3980.0117420814
1074.7352036199 0.0) (11 3980.0117420814 1099.0940271493 0.0))
((0 . "LINE") (100 . "AcDbEntity") (8 . "MASONRY") (62 . 7) (370 . 13) (100 . "AcDbLine") (10 3980.0117420814
1099.0940271493 0.0) (11 3731.1464253394 1099.0940271493 0.0))
((0 . "LINE") (100 . "AcDbEntity") (8 . "MASONRY") (62 . 7) (370 . 13) (100 . "AcDbLine") (10 3751.8852488688
2092.7601809955 0.0) (11 3729.2608144796 2092.7601809955 0.0))
((0 . "LINE") (100 . "AcDbEntity") (8 . "MASONRY") (62 . 7) (370 . 13) (100 . "AcDbLine") (10 3729.2608144796
991.7039140271 0.0) (11 3729.2608144796 1033.1815837104 0.0))
((0 . "LINE") (100 . "AcDbEntity") (8 . "MASONRY") (62 . 7) (370 . 13) (100 . "AcDbLine") (10 3729.2608144796
991.7039140271 0.0) (11 4038.4615384615 991.7039140271 0.0))
((0 . "LINE") (100 . "AcDbEntity") (8 . "MASONRY") (62 . 7) (370 . 13) (100 . "AcDbLine") (10 3750 3052.3364027149 0.0)
(11 3970.5882352941 3052.3364027149 0.0))
((0 . "LINE") (100 . "AcDbEntity") (8 . "MASONRY") (62 . 7) (370 . 13) (100 . "AcDbLine") (10 3970.5882352941
3052.3364027149 0.0) (11 3996.9838687783 3052.3364027149 0.0))
((0 . "LINE") (100 . "AcDbEntity") (8 . "MASONRY") (62 . 7) (370 . 13) (100 . "AcDbLine") (10 3750 3073.1525678733 0.0)
(11 3750 3052.3364027149 0.0))
((0 . "LINE") (100 . "AcDbEntity") (8 . "MASONRY") (62 . 7) (370 . 13) (100 . "AcDbLine") (10 3981.9004524887
1602.7120927602 0.0) (11 3782.0514027149 1602.7120927602 0.0))
((0 . "LINE") (100 . "AcDbEntity") (8 . "MASONRY") (62 . 7) (370 . 13) (100 . "AcDbLine") (10 3782.0514027149
1602.7120927602 0.0) (11 3750 1602.7120927602 0.0))
((0 . "LINE") (100 . "AcDbEntity") (8 . "MASONRY") (62 . 7) (370 . 13) (100 . "AcDbLine") (10 3750 1636.5016742081 0.0)
(11 3750 1602.7120927602 0.0))
((0 . "LINE") (100 . "AcDbEntity") (8 . "MASONRY") (62 . 7) (370 . 13) (100 . "AcDbLine") (10 3893.2883144796
1432.8817647059 0.0) (11 3736.8021832579 1432.8817647059 0.0))
((0 . "LINE") (100 . "AcDbEntity") (8 . "MASONRY") (62 . 7) (370 . 13) (100 . "AcDbLine") (10 3751.8852488688
1336.7265384615 0.0) (11 4019.6083031674 1336.7265384615 0.0))
((0 . "LINE") (100 . "AcDbEntity") (8 . "MASONRY") (62 . 7) (370 . 13) (100 . "AcDbLine") (10 3785.821561086
3137.2546719457 0.0) (11 3759.4269683258 3137.2546719457 0.0))
((0 . "LINE") (100 . "AcDbEntity") (8 . "MASONRY") (62 . 7) (370 . 13) (100 . "AcDbLine") (10 3758.1437782805
1739.5199095023 0.0) (11 3758.1437782805 1677.9793438914 0.0))
((0 . "LINE") (100 . "AcDbEntity") (8 . "MASONRY") (62 . 7) (370 . 13) (100 . "AcDbLine") (10 3758.1437782805
1677.9793438914 0.0) (11 3782.0514027149 1677.9793438914 0.0))
((0 . "LINE") (100 . "AcDbEntity") (8 . "MASONRY") (62 . 7) (370 . 13) (100 . "AcDbLine") (10 3795.2488687783
1739.5199095023 0.0) (11 3758.1437782805 1739.5199095023 0.0))
((0 . "LINE") (100 . "AcDbEntity") (8 . "MASONRY") (62 . 7) (370 . 13) (100 . "AcDbLine") (10 3800.3029072398
2053.1674208145 0.0) (11 3800.3029072398 2090.7979411765 0.0))
((0 . "LINE") (100 . "AcDbEntity") (8 . "MASONRY") (62 . 7) (370 . 13) (100 . "AcDbLine") (10 3800.3029072398
2090.7979411765 0.0) (11 3770.7391855204 2090.7979411765 0.0))
((0 . "LINE") (100 . "AcDbEntity") (8 . "MASONRY") (62 . 7) (370 . 13) (100 . "AcDbLine") (10 3780.1661425339
3472.850678733 0.0) (11 3936.6515837104 3472.850678733 0.0))
((0 . "LINE") (100 . "AcDbEntity") (8 . "MASONRY") (62 . 7) (370 . 13) (100 . "AcDbLine") (10 3780.1661425339
3472.850678733 0.0) (11 3780.1661425339 3487.9334049774 0.0))
((0 . "LINE") (100 . "AcDbEntity") (8 . "MASONRY") (62 . 7) (370 . 13) (100 . "AcDbLine") (10 4000.7536877828
3103.318020362 0.0) (11 3778.2805429864 3103.318020362 0.0))
((0 . "LINE") (100 . "AcDbEntity") (8 . "MASONRY") (62 . 7) (370 . 13) (100 . "AcDbLine") (10 3838.6128280543
1070.8908144796 0.0) (11 3778.2805429864 1070.8908144796 0.0))
((0 . "LINE") (100 . "AcDbEntity") (8 . "MASONRY") (62 . 7) (370 . 13) (100 . "AcDbLine") (10 4038.4615384615
2520.7395248869 0.0) (11 4038.4615384615 2424.5849886878 0.0))
((0 . "LINE") (100 . "AcDbEntity") (8 . "MASONRY") (62 . 7) (370 . 13) (100 . "AcDbLine") (10 4038.4615384615
2424.5849886878 0.0) (11 4038.4615384615 2404.4482239819 0.0))
((0 . "LINE") (100 . "AcDbEntity") (8 . "MASONRY") (62 . 7) (370 . 13) (100 . "AcDbLine") (10 4038.4615384615
2404.4482239819 0.0) (11 3782.0514027149 2404.4482239819 0.0))
((0 . "LINE") (100 . "AcDbEntity") (8 . "MASONRY") (62 . 7) (370 . 13) (100 . "AcDbLine") (10 3797.1337782805
2320.8894343891 0.0) (11 3783.9366515837 2320.8894343891 0.0))
((0 . "LINE") (100 . "AcDbEntity") (8 . "MASONRY") (62 . 7) (370 . 13) (100 . "AcDbLine") (10 3783.9366515837
2352.9411764706 0.0) (11 3783.9366515837 2320.8894343891 0.0))
((0 . "LINE") (100 . "AcDbEntity") (8 . "MASONRY") (62 . 7) (370 . 13) (100 . "AcDbLine") (10 3823.5294117647
2771.4932126697 0.0) (11 3793.363959276 2771.4932126697 0.0))
((0 . "LINE") (100 . "AcDbEntity") (8 . "MASONRY") (62 . 7) (370 . 13) (100 . "AcDbLine") (10 3996.9838687783
2715.0867873303 0.0) (11 3804.6761764706 2715.0867873303 0.0))
((0 . "LINE") (100 . "AcDbEntity") (8 . "MASONRY") (62 . 7) (370 . 13) (100 . "AcDbLine") (10 3804.6761764706
2715.0867873303 0.0) (11 3793.363959276 2715.0867873303 0.0))
((0 . "LINE") (100 . "AcDbEntity") (8 . "MASONRY") (62 . 7) (370 . 13) (100 . "AcDbLine") (10 3795.2488687783
1739.5199095023 0.0) (11 3795.2488687783 1760.9360633484 0.0))
((0 . "LINE") (100 . "AcDbEntity") (8 . "MASONRY") (62 . 7) (370 . 13) (100 . "AcDbLine") (10 3802.7905769231
588.2415045249 0.0) (11 3793.363959276 588.2415045249 0.0))
((0 . "LINE") (100 . "AcDbEntity") (8 . "MASONRY") (62 . 7) (370 . 13) (100 . "AcDbLine") (10 3797.1337782805
2288.8383823529 0.0) (11 3797.1337782805 2320.8894343891 0.0))
((0 . "LINE") (100 . "AcDbEntity") (8 . "MASONRY") (62 . 7) (370 . 13) (100 . "AcDbLine") (10 3797.1337782805
2320.8894343891 0.0) (11 3981.9004524887 2320.8894343891 0.0))
((0 . "LINE") (100 . "AcDbEntity") (8 . "MASONRY") (62 . 7) (370 . 13) (100 . "AcDbLine") (10 3795.2488687783
1739.5199095023 0.0) (11 3917.7945475113 1739.5199095023 0.0))
((0 . "LINE") (100 . "AcDbEntity") (8 . "MASONRY") (62 . 7) (370 . 13) (100 . "AcDbLine") (10 3917.7945475113
1739.5199095023 0.0) (11 3917.7945475113 1711.9146153846 0.0))
((0 . "LINE") (100 . "AcDbEntity") (8 . "MASONRY") (62 . 7) (370 . 13) (100 . "AcDbLine") (10 3959.2760180995
2053.1674208145 0.0) (11 3800.3029072398 2053.1674208145 0.0))
((0 . "LINE") (100 . "AcDbEntity") (8 . "MASONRY") (62 . 7) (370 . 13) (100 . "AcDbLine") (10 3800.9049773756
1817.4971493213 0.0) (11 3800.9049773756 1828.8086764706 0.0))
((0 . "LINE") (100 . "AcDbEntity") (8 . "MASONRY") (62 . 7) (370 . 13) (100 . "AcDbLine") (10 3815.9883936652
1817.4971493213 0.0) (11 3800.9049773756 1817.4971493213 0.0))
((0 . "LINE") (100 . "AcDbEntity") (8 . "MASONRY") (62 . 7) (370 . 13) (100 . "AcDbLine") (10 3868.778280543
1670.4383257919 0.0) (11 3800.9049773756 1670.4383257919 0.0))
((0 . "LINE") (100 . "AcDbEntity") (8 . "MASONRY") (62 . 7) (370 . 13) (100 . "AcDbLine") (10 3802.7905769231
588.2415045249 0.0) (11 3965.569061086 588.2415045249 0.0))
((0 . "LINE") (100 . "AcDbEntity") (8 . "MASONRY") (62 . 7) (370 . 13) (100 . "AcDbLine") (10 3990.9476696833
596.155361991 0.0) (11 4004.5248868778 596.155361991 0.0))
((0 . "LINE") (100 . "AcDbEntity") (8 . "MASONRY") (62 . 7) (370 . 13) (100 . "AcDbLine") (10 3802.7905769231
588.2415045249 0.0) (11 3802.7905769231 599.5475113122 0.0))
((0 . "LINE") (100 . "AcDbEntity") (8 . "MASONRY") (62 . 7) (370 . 13) (100 . "AcDbLine") (10 3810.3315950226
3337.1040723982 0.0) (11 3810.3315950226 3310.7091289593 0.0))
((0 . "LINE") (100 . "AcDbEntity") (8 . "MASONRY") (62 . 7) (370 . 13) (100 . "AcDbLine") (10 3810.3315950226
3337.1040723982 0.0) (11 3981.9004524887 3337.1040723982 0.0))
((0 . "LINE") (100 . "AcDbEntity") (8 . "MASONRY") (62 . 7) (370 . 13) (100 . "AcDbLine") (10 3921.5681674208
2971.3419230769 0.0) (11 3812.2171945701 2971.3419230769 0.0))
((0 . "LINE") (100 . "AcDbEntity") (8 . "MASONRY") (62 . 7) (370 . 13) (100 . "AcDbLine") (10 3849.9250452489
2828.0542986425 0.0) (11 3819.7582126697 2828.0542986425 0.0))
((0 . "LINE") (100 . "AcDbEntity") (8 . "MASONRY") (62 . 7) (370 . 13) (100 . "AcDbLine") (10 3838.6128280543
2777.149321267 0.0) (11 3895.1739140271 2777.149321267 0.0))
((0 . "LINE") (100 . "AcDbEntity") (8 . "MASONRY") (62 . 7) (370 . 13) (100 . "AcDbLine") (10 3842.3826470588
2096.5306900452 0.0) (11 3914.0271493213 2096.5306900452 0.0))
((0 . "LINE") (100 . "AcDbEntity") (8 . "MASONRY") (62 . 7) (370 . 13) (100 . "AcDbLine") (10 4004.5248868778
1815.6108597285 0.0) (11 3842.3826470588 1815.6108597285 0.0))
((0 . "LINE") (100 . "AcDbEntity") (8 . "MASONRY") (62 . 7) (370 . 13) (100 . "AcDbLine") (10 3857.4660633484
1072.7757239819 0.0) (11 3929.1105656109 1072.7757239819 0.0))
((0 . "LINE") (100 . "AcDbEntity") (8 . "MASONRY") (62 . 7) (370 . 13) (100 . "AcDbLine") (10 3876.3192986425
773.0005882353 0.0) (11 3883.8616968326 773.0005882353 0.0))
((0 . "LINE") (100 . "AcDbEntity") (8 . "MASONRY") (62 . 7) (370 . 13) (100 . "AcDbLine") (10 3887.6315158371
859.7285067873 0.0) (11 3887.6315158371 840.8738914027 0.0))
((0 . "LINE") (100 . "AcDbEntity") (8 . "MASONRY") (62 . 7) (370 . 13) (100 . "AcDbLine") (10 3887.6315158371
859.7285067873 0.0) (11 3887.6315158371 938.9140271493 0.0))
((0 . "LINE") (100 . "AcDbEntity") (8 . "MASONRY") (62 . 7) (370 . 13) (100 . "AcDbLine") (10 3889.5171153846
805.1117081448 0.0) (11 3889.5171153846 829.5616742081 0.0))
((0 . "LINE") (100 . "AcDbEntity") (8 . "MASONRY") (62 . 7) (370 . 13) (100 . "AcDbLine") (10 3893.2883144796
1432.8817647059 0.0) (11 4049.7737556561 1432.8817647059 0.0))
((0 . "LINE") (100 . "AcDbEntity") (8 . "MASONRY") (62 . 7) (370 . 13) (100 . "AcDbLine") (10 3893.2883144796
1432.8817647059 0.0) (11 3893.2883144796 1466.8184162896 0.0))
((0 . "LINE") (100 . "AcDbEntity") (8 . "MASONRY") (62 . 7) (370 . 13) (100 . "AcDbLine") (10 4117.6470588235
805.1117081448 0.0) (11 3889.5171153846 805.1117081448 0.0))
((0 . "LINE") (100 . "AcDbEntity") (8 . "MASONRY") (62 . 7) (370 . 13) (100 . "AcDbLine") (10 3974.3594343891
1530.920520362 0.0) (11 3898.9437330317 1530.920520362 0.0))
((0 . "LINE") (100 . "AcDbEntity") (8 . "MASONRY") (62 . 7) (370 . 13) (100 . "AcDbLine") (10 3917.7983484163
1668.5520361991 0.0) (11 3906.4861312217 1668.5520361991 0.0))
((0 . "LINE") (100 . "AcDbEntity") (8 . "MASONRY") (62 . 7) (370 . 13) (100 . "AcDbLine") (10 3923.4544570136
2507.5417081448 0.0) (11 3923.4544570136 2473.6050565611 0.0))
((0 . "LINE") (100 . "AcDbEntity") (8 . "MASONRY") (62 . 7) (370 . 13) (100 . "AcDbLine") (10 3936.6515837104
3472.850678733 0.0) (11 3936.6515837104 3484.1628959276 0.0))
((0 . "LINE") (100 . "AcDbEntity") (8 . "MASONRY") (62 . 7) (370 . 13) (100 . "AcDbLine") (10 3936.6515837104
3472.850678733 0.0) (11 3981.9004524887 3472.850678733 0.0))
((0 . "LINE") (100 . "AcDbEntity") (8 . "MASONRY") (62 . 7) (370 . 13) (100 . "AcDbLine") (10 3951.7343099548
2779.0349208145 0.0) (11 3940.4227828054 2779.0349208145 0.0))
((0 . "LINE") (100 . "AcDbEntity") (8 . "MASONRY") (62 . 7) (370 . 13) (100 . "AcDbLine") (10 4004.5248868778
2779.0349208145 0.0) (11 3951.7343099548 2779.0349208145 0.0))
((0 . "LINE") (100 . "AcDbEntity") (8 . "MASONRY") (62 . 7) (370 . 13) (100 . "AcDbLine") (10 3951.7343099548
2779.0349208145 0.0) (11 3951.7343099548 2828.0542986425 0.0))
((0 . "LINE") (100 . "AcDbEntity") (8 . "MASONRY") (62 . 7) (370 . 13) (100 . "AcDbLine") (10 3953.6199095023
3318.2501470588 0.0) (11 3953.6199095023 3303.1674208145 0.0))
((0 . "LINE") (100 . "AcDbEntity") (8 . "MASONRY") (62 . 7) (370 . 13) (100 . "AcDbLine") (10 3955.5048190045
1657.2398190045 0.0) (11 4019.6083031674 1657.2398190045 0.0))
((0 . "LINE") (100 . "AcDbEntity") (8 . "MASONRY") (62 . 7) (370 . 13) (100 . "AcDbLine") (10 3959.2760180995
2053.1674208145 0.0) (11 3959.2760180995 1998.4919343891 0.0))
((0 . "LINE") (100 . "AcDbEntity") (8 . "MASONRY") (62 . 7) (370 . 13) (100 . "AcDbLine") (10 3959.2760180995
2053.1674208145 0.0) (11 3959.2760180995 2100.3018891403 0.0))
((0 . "LINE") (100 . "AcDbEntity") (8 . "MASONRY") (62 . 7) (370 . 13) (100 . "AcDbLine") (10 3959.2760180995
2100.3018891403 0.0) (11 3970.5882352941 2100.3018891403 0.0))
((0 . "LINE") (100 . "AcDbEntity") (8 . "MASONRY") (62 . 7) (370 . 13) (100 . "AcDbLine") (10 3970.5882352941
2100.3018891403 0.0) (11 4181.7491628959 2100.3018891403 0.0))
((0 . "LINE") (100 . "AcDbEntity") (8 . "MASONRY") (62 . 7) (370 . 13) (100 . "AcDbLine") (10 3983.7860520362
2520.7395248869 0.0) (11 3966.8170361991 2520.7395248869 0.0))
((0 . "LINE") (100 . "AcDbEntity") (8 . "MASONRY") (62 . 7) (370 . 13) (100 . "AcDbLine") (10 3966.8170361991
1742.0814479638 0.0) (11 4061.0859728507 1742.0814479638 0.0))
((0 . "LINE") (100 . "AcDbEntity") (8 . "MASONRY") (62 . 7) (370 . 13) (100 . "AcDbLine") (10 3970.5882352941
2976.9987217195 0.0) (11 3985.6716515837 2976.9987217195 0.0))
((0 . "LINE") (100 . "AcDbEntity") (8 . "MASONRY") (62 . 7) (370 . 13) (100 . "AcDbLine") (10 3981.9004524887
1238.6877828054 0.0) (11 3981.9004524887 1176.4705882353 0.0))
((0 . "LINE") (100 . "AcDbEntity") (8 . "MASONRY") (62 . 7) (370 . 13) (100 . "AcDbLine") (10 3981.9004524887
1568.6283710407 0.0) (11 3981.9004524887 1602.7120927602 0.0))
((0 . "LINE") (100 . "AcDbEntity") (8 . "MASONRY") (62 . 7) (370 . 13) (100 . "AcDbLine") (10 3983.7860520362
2673.4537669683 0.0) (11 3983.7860520362 2620.6638800905 0.0))
((0 . "LINE") (100 . "AcDbEntity") (8 . "MASONRY") (62 . 7) (370 . 13) (100 . "AcDbLine") (10 3983.7860520362
2520.7395248869 0.0) (11 3983.7860520362 2575.4150113122 0.0))
((0 . "LINE") (100 . "AcDbEntity") (8 . "MASONRY") (62 . 7) (370 . 13) (100 . "AcDbLine") (10 3981.9004524887
2320.8894343891 0.0) (11 3981.9004524887 2345.3994683258 0.0))
((0 . "LINE") (100 . "AcDbEntity") (8 . "MASONRY") (62 . 7) (370 . 13) (100 . "AcDbLine") (10 4206.2591968326
2320.8894343891 0.0) (11 3981.9004524887 2320.8894343891 0.0))
((0 . "LINE") (100 . "AcDbEntity") (8 . "MASONRY") (62 . 7) (370 . 13) (100 . "AcDbLine") (10 3981.9004524887
1238.6877828054 0.0) (11 3981.9004524887 1265.0088461538 0.0))
((0 . "LINE") (100 . "AcDbEntity") (8 . "MASONRY") (62 . 7) (370 . 13) (100 . "AcDbLine") (10 3981.9004524887
1265.0088461538 0.0) (11 3981.9004524887 1270.7381447964 0.0))
((0 . "LINE") (100 . "AcDbEntity") (8 . "MASONRY") (62 . 7) (370 . 13) (100 . "AcDbLine") (10 3981.9004524887
1238.6877828054 0.0) (11 4019.6083031674 1238.6877828054 0.0))
((0 . "LINE") (100 . "AcDbEntity") (8 . "MASONRY") (62 . 7) (370 . 13) (100 . "AcDbLine") (10 3983.7860520362
2520.7395248869 0.0) (11 4038.4615384615 2520.7395248869 0.0))
((0 . "LINE") (100 . "AcDbEntity") (8 . "MASONRY") (62 . 7) (370 . 13) (100 . "AcDbLine") (10 3985.6716515837
2375.5656108597 0.0) (11 3985.6716515837 2368.0239027149 0.0))
((0 . "LINE") (100 . "AcDbEntity") (8 . "MASONRY") (62 . 7) (370 . 13) (100 . "AcDbLine") (10 4098.7938235294
1602.7120927602 0.0) (11 3981.9004524887 1602.7120927602 0.0))
((0 . "LINE") (100 . "AcDbEntity") (8 . "MASONRY") (62 . 7) (370 . 13) (100 . "AcDbLine") (10 4012.0659049774
1304.6761764706 0.0) (11 3985.6716515837 1304.6761764706 0.0))
((0 . "LINE") (100 . "AcDbEntity") (8 . "MASONRY") (62 . 7) (370 . 13) (100 . "AcDbLine") (10 3996.9838687783
2473.6050565611 0.0) (11 3989.4414705882 2473.6050565611 0.0))
((0 . "LINE") (100 . "AcDbEntity") (8 . "MASONRY") (62 . 7) (370 . 13) (100 . "AcDbLine") (10 3996.9838687783
637.2539819005 0.0) (11 3996.9838687783 618.4021266968 0.0))
((0 . "LINE") (100 . "AcDbEntity") (8 . "MASONRY") (62 . 7) (370 . 13) (100 . "AcDbLine") (10 4061.0859728507
1964.5545927602 0.0) (11 4000.7536877828 1964.5545927602 0.0))
((0 . "LINE") (100 . "AcDbEntity") (8 . "MASONRY") (62 . 7) (370 . 13) (100 . "AcDbLine") (10 4117.6470588235
656.1085972851 0.0) (11 4008.2960859729 656.1085972851 0.0))
((0 . "LINE") (100 . "AcDbEntity") (8 . "MASONRY") (62 . 7) (370 . 13) (100 . "AcDbLine") (10 4027.149321267
2153.0917760181 0.0) (11 4019.6083031674 2153.0917760181 0.0))
((0 . "LINE") (100 . "AcDbEntity") (8 . "MASONRY") (62 . 7) (370 . 13) (100 . "AcDbLine") (10 4030.920520362
1240.5726923077 0.0) (11 4294.8713348416 1240.5726923077 0.0))
((0 . "LINE") (100 . "AcDbEntity") (8 . "MASONRY") (62 . 7) (370 . 13) (100 . "AcDbLine") (10 4034.6903393665
1336.7265384615 0.0) (11 4198.718178733 1336.7265384615 0.0))
((0 . "LINE") (100 . "AcDbEntity") (8 . "MASONRY") (62 . 7) (370 . 13) (100 . "AcDbLine") (10 4038.4615384615
2621.8680090498 0.0) (11 4407.8457466063 2621.8680090498 0.0))
((0 . "LINE") (100 . "AcDbEntity") (8 . "MASONRY") (62 . 7) (370 . 13) (100 . "AcDbLine") (10 4407.8457466063
2621.8680090498 0.0) (11 4419.3057239819 2621.8680090498 0.0))
((0 . "LINE") (100 . "AcDbEntity") (8 . "MASONRY") (62 . 7) (370 . 13) (100 . "AcDbLine") (10 4038.4615384615
2520.7395248869 0.0) (11 4415.5359049774 2520.7395248869 0.0))
((0 . "LINE") (100 . "AcDbEntity") (8 . "MASONRY") (62 . 7) (370 . 13) (100 . "AcDbLine") (10 4042.2327375566
1817.4957692308 0.0) (11 4051.6593552036 1817.4957692308 0.0))
((0 . "LINE") (100 . "AcDbEntity") (8 . "MASONRY") (62 . 7) (370 . 13) (100 . "AcDbLine") (10 4051.6593552036
1779.787918552 0.0) (11 4051.6593552036 1817.4957692308 0.0))
((0 . "LINE") (100 . "AcDbEntity") (8 . "MASONRY") (62 . 7) (370 . 13) (100 . "AcDbLine") (10 4117.6470588235
1817.4957692308 0.0) (11 4064.8571719457 1817.4957692308 0.0))
((0 . "LINE") (100 . "AcDbEntity") (8 . "MASONRY") (62 . 7) (370 . 13) (100 . "AcDbLine") (10 4064.8571719457
1817.4957692308 0.0) (11 4051.6593552036 1817.4957692308 0.0))
((0 . "LINE") (100 . "AcDbEntity") (8 . "MASONRY") (62 . 7) (370 . 13) (100 . "AcDbLine") (10 4095.0226244344
591.9291628959 0.0) (11 4057.3154638009 591.9291628959 0.0))
((0 . "LINE") (100 . "AcDbEntity") (8 . "MASONRY") (62 . 7) (370 . 13) (100 . "AcDbLine") (10 4057.3154638009
591.9291628959 0.0) (11 4057.3154638009 554.2986425339 0.0))
((0 . "LINE") (100 . "AcDbEntity") (8 . "MASONRY") (62 . 7) (370 . 13) (100 . "AcDbLine") (10 4061.0859728507
1964.5545927602 0.0) (11 4061.0859728507 1945.7013574661 0.0))
((0 . "LINE") (100 . "AcDbEntity") (8 . "MASONRY") (62 . 7) (370 . 13) (100 . "AcDbLine") (10 4061.0859728507
1964.5545927602 0.0) (11 4234.5404298643 1964.5545927602 0.0))
((0 . "LINE") (100 . "AcDbEntity") (8 . "MASONRY") (62 . 7) (370 . 13) (100 . "AcDbLine") (10 4087.4816063348
976.6218778281 0.0) (11 4072.3981900452 976.6218778281 0.0))
((0 . "LINE") (100 . "AcDbEntity") (8 . "MASONRY") (62 . 7) (370 . 13) (100 . "AcDbLine") (10 4076.1693891403
1743.9663574661 0.0) (11 4294.8713348416 1743.9663574661 0.0))
((0 . "LINE") (100 . "AcDbEntity") (8 . "MASONRY") (62 . 7) (370 . 13) (100 . "AcDbLine") (10 4151.5837104072
1470.5882352941 0.0) (11 4083.7104072398 1470.5882352941 0.0))
((0 . "LINE") (100 . "AcDbEntity") (8 . "MASONRY") (62 . 7) (370 . 13) (100 . "AcDbLine") (10 4087.4816063348
1647.8138914027 0.0) (11 4098.7938235294 1647.8138914027 0.0))
((0 . "LINE") (100 . "AcDbEntity") (8 . "MASONRY") (62 . 7) (370 . 13) (100 . "AcDbLine") (10 4098.7938235294
1602.7120927602 0.0) (11 4294.8713348416 1602.7120927602 0.0))
((0 . "LINE") (100 . "AcDbEntity") (8 . "MASONRY") (62 . 7) (370 . 13) (100 . "AcDbLine") (10 4098.7938235294
1602.7120927602 0.0) (11 4098.7938235294 1647.8138914027 0.0))
((0 . "LINE") (100 . "AcDbEntity") (8 . "MASONRY") (62 . 7) (370 . 13) (100 . "AcDbLine") (10 4087.4816063348
1425.3393665158 0.0) (11 4200.6037782805 1425.3393665158 0.0))
((0 . "LINE") (100 . "AcDbEntity") (8 . "MASONRY") (62 . 7) (370 . 13) (100 . "AcDbLine") (10 4096.9082239819
2198.3406447964 0.0) (11 4249.6262669683 2198.3406447964 0.0))
((0 . "LINE") (100 . "AcDbEntity") (8 . "MASONRY") (62 . 7) (370 . 13) (100 . "AcDbLine") (10 4096.9082239819
2198.3406447964 0.0) (11 4096.9082239819 2220.9650791855 0.0))
((0 . "LINE") (100 . "AcDbEntity") (8 . "MASONRY") (62 . 7) (370 . 13) (100 . "AcDbLine") (10 4106.334841629
595.7776923077 0.0) (11 4113.8758597285 595.7776923077 0.0))
((0 . "LINE") (100 . "AcDbEntity") (8 . "MASONRY") (62 . 7) (370 . 13) (100 . "AcDbLine") (10 4121.4182579186
1930.6186312217 0.0) (11 4110.106040724 1930.6186312217 0.0))
((0 . "LINE") (100 . "AcDbEntity") (8 . "MASONRY") (62 . 7) (370 . 13) (100 . "AcDbLine") (10 4098.7938235294
1647.8138914027 0.0) (11 4117.6470588235 1647.8138914027 0.0))
((0 . "LINE") (100 . "AcDbEntity") (8 . "MASONRY") (62 . 7) (370 . 13) (100 . "AcDbLine") (10 4121.4182579186
1885.3697624434 0.0) (11 4121.4182579186 1862.7453280543 0.0))
((0 . "LINE") (100 . "AcDbEntity") (8 . "MASONRY") (62 . 7) (370 . 13) (100 . "AcDbLine") (10 4134.6153846154
558.0684615385 0.0) (11 4134.6153846154 565.6108597285 0.0))
((0 . "LINE") (100 . "AcDbEntity") (8 . "MASONRY") (62 . 7) (370 . 13) (100 . "AcDbLine") (10 4152.5613800905 1075.8475
0.0) (11 4140.2714932127 1075.8475 0.0))
((0 . "LINE") (100 . "AcDbEntity") (8 . "MASONRY") (62 . 7) (370 . 13) (100 . "AcDbLine") (10 4149.6981108597
1123.679321267 0.0) (11 4149.6981108597 1112.3671040724 0.0))
((0 . "LINE") (100 . "AcDbEntity") (8 . "MASONRY") (62 . 7) (370 . 13) (100 . "AcDbLine") (10 4223.2282126697
2658.371040724 0.0) (11 4196.8325791855 2658.371040724 0.0))
((0 . "LINE") (100 . "AcDbEntity") (8 . "MASONRY") (62 . 7) (370 . 13) (100 . "AcDbLine") (10 4200.6037782805
1425.3393665158 0.0) (11 4200.6037782805 1401.3575226244 0.0))
((0 . "LINE") (100 . "AcDbEntity") (8 . "MASONRY") (62 . 7) (370 . 13) (100 . "AcDbLine") (10 4200.6037782805
1401.3575226244 0.0) (11 4294.8713348416 1401.3575226244 0.0))
((0 . "LINE") (100 . "AcDbEntity") (8 . "MASONRY") (62 . 7) (370 . 13) (100 . "AcDbLine") (10 4200.6037782805
1425.3393665158 0.0) (11 4200.6037782805 1436.6515837104 0.0))
((0 . "LINE") (100 . "AcDbEntity") (8 . "MASONRY") (62 . 7) (370 . 13) (100 . "AcDbLine") (10 4213.8009049774
1336.7265384615 0.0) (11 4198.718178733 1336.7265384615 0.0))
((0 . "LINE") (100 . "AcDbEntity") (8 . "MASONRY") (62 . 7) (370 . 13) (100 . "AcDbLine") (10 4198.718178733
1365.0084615385 0.0) (11 4198.718178733 1336.7265384615 0.0))
((0 . "LINE") (100 . "AcDbEntity") (8 . "MASONRY") (62 . 7) (370 . 13) (100 . "AcDbLine") (10 4200.6037782805
1472.4745248869 0.0) (11 4230.7692307692 1472.4745248869 0.0))
((0 . "LINE") (100 . "AcDbEntity") (8 . "MASONRY") (62 . 7) (370 . 13) (100 . "AcDbLine") (10 4206.2591968326
2320.8894343891 0.0) (11 4457.0135746606 2320.8894343891 0.0))
((0 . "LINE") (100 . "AcDbEntity") (8 . "MASONRY") (62 . 7) (370 . 13) (100 . "AcDbLine") (10 4206.2591968326
2320.8894343891 0.0) (11 4206.2591968326 2371.79510181 0.0))
((0 . "LINE") (100 . "AcDbEntity") (8 . "MASONRY") (62 . 7) (370 . 13) (100 . "AcDbLine") (10 4213.8009049774
1336.7265384615 0.0) (11 4213.8009049774 1293.3625791855 0.0))
((0 . "LINE") (100 . "AcDbEntity") (8 . "MASONRY") (62 . 7) (370 . 13) (100 . "AcDbLine") (10 4215.7631447964
2466.0633484163 0.0) (11 4215.7631447964 2410.0270022624 0.0))
((0 . "LINE") (100 . "AcDbEntity") (8 . "MASONRY") (62 . 7) (370 . 13) (100 . "AcDbLine") (10 4215.7631447964
2410.0270022624 0.0) (11 4460.7847737557 2410.0270022624 0.0))
((0 . "LINE") (100 . "AcDbEntity") (8 . "MASONRY") (62 . 7) (370 . 13) (100 . "AcDbLine") (10 4460.7847737557
2410.0270022624 0.0) (11 4460.7847737557 2386.8778280543 0.0))
((0 . "LINE") (100 . "AcDbEntity") (8 . "MASONRY") (62 . 7) (370 . 13) (100 . "AcDbLine") (10 4460.7847737557
2386.8778280543 0.0) (11 4460.7847737557 2371.79510181 0.0))
((0 . "LINE") (100 . "AcDbEntity") (8 . "MASONRY") (62 . 7) (370 . 13) (100 . "AcDbLine") (10 4215.6858144796
1826.9230769231 0.0) (11 4294.8713348416 1826.9230769231 0.0))
((0 . "LINE") (100 . "AcDbEntity") (8 . "MASONRY") (62 . 7) (370 . 13) (100 . "AcDbLine") (10 4213.8009049774
1336.7265384615 0.0) (11 4294.8713348416 1336.7265384615 0.0))
((0 . "LINE") (100 . "AcDbEntity") (8 . "MASONRY") (62 . 7) (370 . 13) (100 . "AcDbLine") (10 4223.2282126697
1700.60239819 0.0) (11 4223.2282126697 1685.520361991 0.0))
((0 . "LINE") (100 . "AcDbEntity") (8 . "MASONRY") (62 . 7) (370 . 13) (100 . "AcDbLine") (10 4298.6425339367
1657.2398190045 0.0) (11 4226.9980316742 1657.2398190045 0.0))
((0 . "LINE") (100 . "AcDbEntity") (8 . "MASONRY") (62 . 7) (370 . 13) (100 . "AcDbLine") (10 4230.7692307692
2113.4997058824 0.0) (11 4298.6425339367 2113.4997058824 0.0))
((0 . "LINE") (100 . "AcDbEntity") (8 . "MASONRY") (62 . 7) (370 . 13) (100 . "AcDbLine") (10 4234.5404298643
2026.7717873303 0.0) (11 4234.5404298643 1964.5545927602 0.0))
((0 . "LINE") (100 . "AcDbEntity") (8 . "MASONRY") (62 . 7) (370 . 13) (100 . "AcDbLine") (10 4234.5404298643
2066.3652375566 0.0) (11 4234.5404298643 2026.7717873303 0.0))
((0 . "LINE") (100 . "AcDbEntity") (8 . "MASONRY") (62 . 7) (370 . 13) (100 . "AcDbLine") (10 4294.8713348416
2026.7717873303 0.0) (11 4234.5404298643 2026.7717873303 0.0))
((0 . "LINE") (100 . "AcDbEntity") (8 . "MASONRY") (62 . 7) (370 . 13) (100 . "AcDbLine") (10 4294.8713348416
1964.5545927602 0.0) (11 4234.5404298643 1964.5545927602 0.0))
((0 . "LINE") (100 . "AcDbEntity") (8 . "MASONRY") (62 . 7) (370 . 13) (100 . "AcDbLine") (10 4298.6425339367
2198.3406447964 0.0) (11 4249.6262669683 2198.3406447964 0.0))
((0 . "LINE") (100 . "AcDbEntity") (8 . "MASONRY") (62 . 7) (370 . 13) (100 . "AcDbLine") (10 4298.6425339367
2225.4978393665 0.0) (11 4249.6262669683 2225.4978393665 0.0))
((0 . "LINE") (100 . "AcDbEntity") (8 . "MASONRY") (62 . 7) (370 . 13) (100 . "AcDbLine") (10 4249.6262669683
2225.4978393665 0.0) (11 4249.6262669683 2198.3406447964 0.0))
((0 . "LINE") (100 . "AcDbEntity") (8 . "MASONRY") (62 . 7) (370 . 13) (100 . "AcDbLine") (10 4294.8713348416
1466.8184162896 0.0) (11 4249.6224660633 1466.8184162896 0.0))
((0 . "LINE") (100 . "AcDbEntity") (8 . "MASONRY") (62 . 7) (370 . 13) (100 . "AcDbLine") (10 4260.9346832579
2662.1415497738 0.0) (11 4370.2870361991 2662.1415497738 0.0))
((0 . "LINE") (100 . "AcDbEntity") (8 . "MASONRY") (62 . 7) (370 . 13) (100 . "AcDbLine") (10 6541.2509276018
2205.8823529412 0.0) (11 6541.2509276018 2273.7556561086 0.0))
((0 . "LINE") (100 . "AcDbEntity") (8 . "MASONRY") (62 . 7) (370 . 13) (100 . "AcDbLine") (10 6541.2509276018
2273.7556561086 0.0) (11 6541.2509276018 2313.2738461538 0.0))
((0 . "LINE") (100 . "AcDbEntity") (8 . "MASONRY") (62 . 7) (370 . 13) (100 . "AcDbLine") (10 6541.2509276018
2313.2738461538 0.0) (11 6541.2509276018 2348.1142873303 0.0))
((0 . "LINE") (100 . "AcDbEntity") (8 . "MASONRY") (62 . 7) (370 . 13) (100 . "AcDbLine") (10 6541.2509276018
2348.1142873303 0.0) (11 6459.2760180995 2348.1142873303 0.0))
((0 . "LINE") (100 . "AcDbEntity") (8 . "MASONRY") (62 . 7) (370 . 13) (100 . "AcDbLine") (10 6459.2760180995
2348.1142873303 0.0) (11 6097.2850678733 2348.1142873303 0.0))
((0 . "LINE") (100 . "AcDbEntity") (8 . "MASONRY") (62 . 7) (370 . 13) (100 . "AcDbLine") (10 6097.2850678733
2348.1142873303 0.0) (11 5958.1149095023 2348.1142873303 0.0))
((0 . "LINE") (100 . "AcDbEntity") (8 . "MASONRY") (62 . 7) (370 . 13) (100 . "AcDbLine") (10 4912.9258144796
2348.1142873303 0.0) (11 4766.214638009 2348.1142873303 0.0))
((0 . "LINE") (100 . "AcDbEntity") (8 . "MASONRY") (62 . 7) (370 . 13) (100 . "AcDbLine") (10 4766.214638009
2348.1142873303 0.0) (11 4472.0969909502 2348.1142873303 0.0))
((0 . "LINE") (100 . "AcDbEntity") (8 . "MASONRY") (62 . 7) (370 . 13) (100 . "AcDbLine") (10 4472.0969909502
2348.1142873303 0.0) (11 4457.0135746606 2348.1142873303 0.0))
((0 . "LINE") (100 . "AcDbEntity") (8 . "MASONRY") (62 . 7) (370 . 13) (100 . "AcDbLine") (10 4457.0135746606
2348.1142873303 0.0) (11 4374.0568552036 2348.1142873303 0.0))
((0 . "LINE") (100 . "AcDbEntity") (8 . "MASONRY") (62 . 7) (370 . 13) (100 . "AcDbLine") (10 4374.0568552036
2348.1142873303 0.0) (11 4355.2550565611 2348.1142873303 0.0))
((0 . "LINE") (100 . "AcDbEntity") (8 . "MASONRY") (62 . 7) (370 . 13) (100 . "AcDbLine") (10 5015.0834162896
2665.9127488688 0.0) (11 4562.5947285068 2665.9127488688 0.0))
((0 . "LINE") (100 . "AcDbEntity") (8 . "MASONRY") (62 . 7) (370 . 13) (100 . "AcDbLine") (10 4562.5947285068
2665.9127488688 0.0) (11 4407.9935067873 2665.9127488688 0.0))
((0 . "LINE") (100 . "AcDbEntity") (8 . "MASONRY") (62 . 7) (370 . 13) (100 . "AcDbLine") (10 4607.8435972851
2575.414321267 0.0) (11 4419.3057239819 2575.414321267 0.0))
((0 . "LINE") (100 . "AcDbEntity") (8 . "MASONRY") (62 . 7) (370 . 13) (100 . "AcDbLine") (10 4457.0135746606
2349.1706674208 0.0) (11 4457.0135746606 2348.1142873303 0.0))
((0 . "LINE") (100 . "AcDbEntity") (8 . "MASONRY") (62 . 7) (370 . 13) (100 . "AcDbLine") (10 4457.0135746606
2348.1142873303 0.0) (11 4457.0135746606 2320.8894343891 0.0))
((0 . "LINE") (100 . "AcDbEntity") (8 . "MASONRY") (62 . 7) (370 . 13) (100 . "AcDbLine") (10 4528.6580769231
2320.8894343891 0.0) (11 4457.0135746606 2320.8894343891 0.0))
((0 . "LINE") (100 . "AcDbEntity") (8 . "MASONRY") (62 . 7) (370 . 13) (100 . "AcDbLine") (10 4464.5545927602
2439.6684049774 0.0) (11 4464.5545927602 2530.1661425339 0.0))
((0 . "LINE") (100 . "AcDbEntity") (8 . "MASONRY") (62 . 7) (370 . 13) (100 . "AcDbLine") (10 4464.5545927602
2631.9760972851 0.0) (11 4477.7524095023 2631.9760972851 0.0))
((0 . "LINE") (100 . "AcDbEntity") (8 . "MASONRY") (62 . 7) (370 . 13) (100 . "AcDbLine") (10 4464.5545927602
2549.0193778281 0.0) (11 4464.5545927602 2530.1661425339 0.0))
((0 . "LINE") (100 . "AcDbEntity") (8 . "MASONRY") (62 . 7) (370 . 13) (100 . "AcDbLine") (10 4973.6043665158
2530.1661425339 0.0) (11 4464.5545927602 2530.1661425339 0.0))
((0 . "LINE") (100 . "AcDbEntity") (8 . "MASONRY") (62 . 7) (370 . 13) (100 . "AcDbLine") (10 4477.7524095023
2631.9760972851 0.0) (11 4477.7524095023 2620.6638800905 0.0))
((0 . "LINE") (100 . "AcDbEntity") (8 . "MASONRY") (62 . 7) (370 . 13) (100 . "AcDbLine") (10 4477.7524095023
2631.9760972851 0.0) (11 4521.115678733 2631.9760972851 0.0))
((0 . "LINE") (100 . "AcDbEntity") (8 . "MASONRY") (62 . 7) (370 . 13) (100 . "AcDbLine") (10 4604.07239819
2633.8616968326 0.0) (11 4834.0879411765 2633.8616968326 0.0))
((0 . "LINE") (100 . "AcDbEntity") (8 . "MASONRY") (62 . 7) (370 . 13) (100 . "AcDbLine") (10 4607.8435972851
490.195158371 0.0) (11 4613.4990158371 490.195158371 0.0))
((0 . "LINE") (100 . "AcDbEntity") (8 . "MASONRY") (62 . 7) (370 . 13) (100 . "AcDbLine") (10 4613.4990158371
512.8195927602 0.0) (11 4613.4990158371 490.195158371 0.0))
((0 . "LINE") (100 . "AcDbEntity") (8 . "MASONRY") (62 . 7) (370 . 13) (100 . "AcDbLine") (10 4613.4990158371
490.195158371 0.0) (11 4622.9256334842 490.195158371 0.0))
((0 . "LINE") (100 . "AcDbEntity") (8 . "MASONRY") (62 . 7) (370 . 13) (100 . "AcDbLine") (10 4637.1328733032
467.5707239819 0.0) (11 4637.1328733032 454.7899321267 0.0))
((0 . "LINE") (100 . "AcDbEntity") (8 . "MASONRY") (62 . 7) (370 . 13) (100 . "AcDbLine") (10 4692.8436425339
2217.9706334842 0.0) (11 4653.9855542986 2217.9706334842 0.0))
((0 . "LINE") (100 . "AcDbEntity") (8 . "MASONRY") (62 . 7) (370 . 13) (100 . "AcDbLine") (10 4664.4046832579
514.7058823529 0.0) (11 4773.7556561086 514.7058823529 0.0))
((0 . "LINE") (100 . "AcDbEntity") (8 . "MASONRY") (62 . 7) (370 . 13) (100 . "AcDbLine") (10 4717.1945701357
2269.9851470588 0.0) (11 4705.8823529412 2269.9851470588 0.0))
((0 . "LINE") (100 . "AcDbEntity") (8 . "MASONRY") (62 . 7) (370 . 13) (100 . "AcDbLine") (10 4762.443438914
2292.609581448 0.0) (11 4777.5268552036 2292.609581448 0.0))
((0 . "LINE") (100 . "AcDbEntity") (8 . "MASONRY") (62 . 7) (370 . 13) (100 . "AcDbLine") (10 4792.6088914027
2305.80739819 0.0) (11 4807.6923076923 2305.80739819 0.0))
((0 . "LINE") (100 . "AcDbEntity") (8 . "MASONRY") (62 . 7) (370 . 13) (100 . "AcDbLine") (10 4819.0045248869
2579.185520362 0.0) (11 4834.0879411765 2579.185520362 0.0))
((0 . "LINE") (100 . "AcDbEntity") (8 . "MASONRY") (62 . 7) (370 . 13) (100 . "AcDbLine") (10 4834.0879411765
2579.185520362 0.0) (11 5009.4266176471 2579.185520362 0.0))
((0 . "LINE") (100 . "AcDbEntity") (8 . "MASONRY") (62 . 7) (370 . 13) (100 . "AcDbLine") (10 4822.7757239819
2317.1196153846 0.0) (11 4837.857760181 2317.1196153846 0.0))
((0 . "LINE") (100 . "AcDbEntity") (8 . "MASONRY") (62 . 7) (370 . 13) (100 . "AcDbLine") (10 4852.9411764706
2633.8616968326 0.0) (11 4996.228800905 2633.8616968326 0.0))
((0 . "LINE") (100 . "AcDbEntity") (8 . "MASONRY") (62 . 7) (370 . 13) (100 . "AcDbLine") (10 4856.7123755656
2329.1174434389 0.0) (11 4873.508540724 2329.1174434389 0.0))
((0 . "LINE") (100 . "AcDbEntity") (8 . "MASONRY") (62 . 7) (370 . 13) (100 . "AcDbLine") (10 5009.4266176471
2556.5610859729 0.0) (11 5009.4266176471 2579.185520362 0.0))
((0 . "LINE") (100 . "AcDbEntity") (8 . "MASONRY") (62 . 7) (370 . 13) (100 . "AcDbLine") (10 5009.4266176471
2579.185520362 0.0) (11 5018.8532352941 2579.185520362 0.0))
((0 . "LINE") (100 . "AcDbEntity") (8 . "MASONRY") (62 . 7) (370 . 13) (100 . "AcDbLine") (10 5678.7330316742
2526.3949434389 0.0) (11 5015.0834162896 2526.3949434389 0.0))
((0 . "LINE") (100 . "AcDbEntity") (8 . "MASONRY") (62 . 7) (370 . 13) (100 . "AcDbLine") (10 5018.8532352941
2594.2682466063 0.0) (11 5018.8532352941 2579.185520362 0.0))
((0 . "LINE") (100 . "AcDbEntity") (8 . "MASONRY") (62 . 7) (370 . 13) (100 . "AcDbLine") (10 5018.8532352941
2579.185520362 0.0) (11 5203.6199095023 2579.185520362 0.0))
((0 . "LINE") (100 . "AcDbEntity") (8 . "MASONRY") (62 . 7) (370 . 13) (100 . "AcDbLine") (10 5024.5100339367
2477.3755656109 0.0) (11 5024.5100339367 2492.4582918552 0.0))
((0 . "LINE") (100 . "AcDbEntity") (8 . "MASONRY") (62 . 7) (370 . 13) (100 . "AcDbLine") (10 5682.5042307692
2665.9127488688 0.0) (11 5026.3956334842 2665.9127488688 0.0))
((0 . "LINE") (100 . "AcDbEntity") (8 . "MASONRY") (62 . 7) (370 . 13) (100 . "AcDbLine") (10 5071.6445022624
2631.9760972851 0.0) (11 5026.3956334842 2631.9760972851 0.0))
((0 . "LINE") (100 . "AcDbEntity") (8 . "MASONRY") (62 . 7) (370 . 13) (100 . "AcDbLine") (10 5082.956719457
2631.9760972851 0.0) (11 5180.9954751131 2631.9760972851 0.0))
((0 . "LINE") (100 . "AcDbEntity") (8 . "MASONRY") (62 . 7) (370 . 13) (100 . "AcDbLine") (10 5092.1230429864
524.1318099548 0.0) (11 5092.1230429864 490.0039027149 0.0))
((0 . "LINE") (100 . "AcDbEntity") (8 . "MASONRY") (62 . 7) (370 . 13) (100 . "AcDbLine") (10 5290.3464479638
516.5921719457 0.0) (11 5154.599841629 516.5921719457 0.0))
((0 . "LINE") (100 . "AcDbEntity") (8 . "MASONRY") (62 . 7) (370 . 13) (100 . "AcDbLine") (10 5663.6496153846
2631.9760972851 0.0) (11 5207.3911085973 2631.9760972851 0.0))
((0 . "LINE") (100 . "AcDbEntity") (8 . "MASONRY") (62 . 7) (370 . 13) (100 . "AcDbLine") (10 5577.0611651584
516.5921719457 0.0) (11 5577.0611651584 505.3165497738 0.0))
((0 . "LINE") (100 . "AcDbEntity") (8 . "MASONRY") (62 . 7) (370 . 13) (100 . "AcDbLine") (10 5625.9431447964
516.5921719457 0.0) (11 5769.2307692308 516.5921719457 0.0))
((0 . "LINE") (100 . "AcDbEntity") (8 . "MASONRY") (62 . 7) (370 . 13) (100 . "AcDbLine") (10 5678.7330316742
2526.3949434389 0.0) (11 5678.7330316742 2560.3315950226 0.0))
((0 . "LINE") (100 . "AcDbEntity") (8 . "MASONRY") (62 . 7) (370 . 13) (100 . "AcDbLine") (10 5678.7330316742
2526.3949434389 0.0) (11 5940.7989366516 2526.3949434389 0.0))
((0 . "LINE") (100 . "AcDbEntity") (8 . "MASONRY") (62 . 7) (370 . 13) (100 . "AcDbLine") (10 5690.0452488688
2635.7466063348 0.0) (11 5682.5042307692 2635.7466063348 0.0))
((0 . "LINE") (100 . "AcDbEntity") (8 . "MASONRY") (62 . 7) (370 . 13) (100 . "AcDbLine") (10 5690.0452488688
2603.6948642534 0.0) (11 5682.5042307692 2603.6948642534 0.0))
((0 . "LINE") (100 . "AcDbEntity") (8 . "MASONRY") (62 . 7) (370 . 13) (100 . "AcDbLine") (10 5712.6696832579
2665.9127488688 0.0) (11 5697.5862669683 2665.9127488688 0.0))
((0 . "LINE") (100 . "AcDbEntity") (8 . "MASONRY") (62 . 7) (370 . 13) (100 . "AcDbLine") (10 5908.7478846154
2631.9760972851 0.0) (11 5814.4796380091 2631.9760972851 0.0))
((0 . "LINE") (100 . "AcDbEntity") (8 . "MASONRY") (62 . 7) (370 . 13) (100 . "AcDbLine") (10 5814.4796380091
2631.9760972851 0.0) (11 5739.0653167421 2631.9760972851 0.0))
((0 . "LINE") (100 . "AcDbEntity") (8 . "MASONRY") (62 . 7) (370 . 13) (100 . "AcDbLine") (10 5761.6897511312
2664.0271493213 0.0) (11 6119.9095022624 2664.0271493213 0.0))
((0 . "LINE") (100 . "AcDbEntity") (8 . "MASONRY") (62 . 7) (370 . 13) (100 . "AcDbLine") (10 6150.0756447964
2321.7897737557 0.0) (11 6011.8454411765 2321.7897737557 0.0))
((0 . "LINE") (100 . "AcDbEntity") (8 . "MASONRY") (62 . 7) (370 . 13) (100 . "AcDbLine") (10 5855.9579977376
508.9724434389 0.0) (11 5823.7840497738 508.9724434389 0.0))
((0 . "LINE") (100 . "AcDbEntity") (8 . "MASONRY") (62 . 7) (370 . 13) (100 . "AcDbLine") (10 5823.7840497738
508.9724434389 0.0) (11 5823.7840497738 480.0408144796 0.0))
((0 . "LINE") (100 . "AcDbEntity") (8 . "MASONRY") (62 . 7) (370 . 13) (100 . "AcDbLine") (10 5855.9579977376
499.3863348416 0.0) (11 5855.9579977376 508.9724434389 0.0))
((0 . "LINE") (100 . "AcDbEntity") (8 . "MASONRY") (62 . 7) (370 . 13) (100 . "AcDbLine") (10 5855.9579977376
520.3619909502 0.0) (11 5855.9579977376 508.9724434389 0.0))
((0 . "LINE") (100 . "AcDbEntity") (8 . "MASONRY") (62 . 7) (370 . 13) (100 . "AcDbLine") (10 6251.8855995475
2241.4263574661 0.0) (11 6145.3826470588 2241.4263574661 0.0))
((0 . "LINE") (100 . "AcDbEntity") (8 . "MASONRY") (62 . 7) (370 . 13) (100 . "AcDbLine") (10 5937.0284276018
2616.8926809955 0.0) (11 5937.0284276018 2633.8616968326 0.0))
((0 . "LINE") (100 . "AcDbEntity") (8 . "MASONRY") (62 . 7) (370 . 13) (100 . "AcDbLine") (10 5937.0284276018
2633.8616968326 0.0) (11 6425.3393665158 2633.8616968326 0.0))
((0 . "LINE") (100 . "AcDbEntity") (8 . "MASONRY") (62 . 7) (370 . 13) (100 . "AcDbLine") (10 5940.7989366516
2537.7071606335 0.0) (11 5940.7989366516 2526.3949434389 0.0))
((0 . "LINE") (100 . "AcDbEntity") (8 . "MASONRY") (62 . 7) (370 . 13) (100 . "AcDbLine") (10 6293.3632692308
2526.3949434389 0.0) (11 5940.7989366516 2526.3949434389 0.0))
((0 . "LINE") (100 . "AcDbEntity") (8 . "MASONRY") (62 . 7) (370 . 13) (100 . "AcDbLine") (10 6342.3833371041
2662.1415497738 0.0) (11 6131.221719457 2662.1415497738 0.0))
((0 . "LINE") (100 . "AcDbEntity") (8 . "MASONRY") (62 . 7) (370 . 13) (100 . "AcDbLine") (10 6161.387861991
516.5921719457 0.0) (11 6180.2410972851 516.5921719457 0.0))
((0 . "LINE") (100 . "AcDbEntity") (8 . "MASONRY") (62 . 7) (370 . 13) (100 . "AcDbLine") (10 6329.185520362
2398.1900452489 0.0) (11 6329.185520362 2385.0702488688 0.0))
((0 . "LINE") (100 . "AcDbEntity") (8 . "MASONRY") (62 . 7) (370 . 13) (100 . "AcDbLine") (10 6329.185520362
2385.0702488688 0.0) (11 6210.407239819 2385.0702488688 0.0))
((0 . "LINE") (100 . "AcDbEntity") (8 . "MASONRY") (62 . 7) (370 . 13) (100 . "AcDbLine") (10 6261.6691742081
483.788540724 0.0) (11 6261.6691742081 535.4440271493 0.0))
((0 . "LINE") (100 . "AcDbEntity") (8 . "MASONRY") (62 . 7) (370 . 13) (100 . "AcDbLine") (10 6263.1978167421
2573.5294117647 0.0) (11 6338.612138009 2573.5294117647 0.0))
((0 . "LINE") (100 . "AcDbEntity") (8 . "MASONRY") (62 . 7) (370 . 13) (100 . "AcDbLine") (10 6334.8416289593
2435.8972058824 0.0) (11 6334.8416289593 2443.4389140271 0.0))
((0 . "LINE") (100 . "AcDbEntity") (8 . "MASONRY") (62 . 7) (370 . 13) (100 . "AcDbLine") (10 6649.6981108597
2573.5294117647 0.0) (11 6338.612138009 2573.5294117647 0.0))
((0 . "LINE") (100 . "AcDbEntity") (8 . "MASONRY") (62 . 7) (370 . 13) (100 . "AcDbLine") (10 6852.7898303167
2498.037760181 0.0) (11 6647.8132013575 2498.037760181 0.0))
((0 . "LINE") (100 . "AcDbEntity") (8 . "MASONRY") (62 . 7) (370 . 13) (100 . "AcDbLine") (10 6647.8132013575
2498.037760181 0.0) (11 6647.8132013575 2473.7597171946 0.0))
((0 . "LINE") (100 . "AcDbEntity") (8 . "MASONRY") (62 . 7) (370 . 13) (100 . "AcDbLine") (10 6647.8132013575
2473.7597171946 0.0) (11 6338.612138009 2473.7597171946 0.0))
((0 . "LINE") (100 . "AcDbEntity") (8 . "MASONRY") (62 . 7) (370 . 13) (100 . "AcDbLine") (10 6338.612138009
2473.7597171946 0.0) (11 6338.612138009 2522.6244343891 0.0))
((0 . "LINE") (100 . "AcDbEntity") (8 . "MASONRY") (62 . 7) (370 . 13) (100 . "AcDbLine") (10 6338.612138009
2522.6244343891 0.0) (11 6338.612138009 2573.5294117647 0.0))
((0 . "LINE") (100 . "AcDbEntity") (8 . "MASONRY") (62 . 7) (370 . 13) (100 . "AcDbLine") (10 6500.7543778281
2386.8778280543 0.0) (11 6383.8610067873 2386.8778280543 0.0))
((0 . "LINE") (100 . "AcDbEntity") (8 . "MASONRY") (62 . 7) (370 . 13) (100 . "AcDbLine") (10 6527.149321267
2664.0271493213 0.0) (11 6402.7149321267 2664.0271493213 0.0))
((0 . "LINE") (100 . "AcDbEntity") (8 . "MASONRY") (62 . 7) (370 . 13) (100 . "AcDbLine") (10 6419.3449434389
531.6093099548 0.0) (11 6419.3449434389 565.6108597285 0.0))
((0 . "LINE") (100 . "AcDbEntity") (8 . "MASONRY") (62 . 7) (370 . 13) (100 . "AcDbLine") (10 6429.1098755656
2303.9211085973 0.0) (11 6512.0665950226 2303.9211085973 0.0))
((0 . "LINE") (100 . "AcDbEntity") (8 . "MASONRY") (62 . 7) (370 . 13) (100 . "AcDbLine") (10 6645.92760181
2635.7466063348 0.0) (11 6444.1932918552 2635.7466063348 0.0))
((0 . "LINE") (100 . "AcDbEntity") (8 . "MASONRY") (62 . 7) (370 . 13) (100 . "AcDbLine") (10 6527.149321267
2313.2738461538 0.0) (11 6541.2509276018 2313.2738461538 0.0))
((0 . "LINE") (100 . "AcDbEntity") (8 . "MASONRY") (62 . 7) (370 . 13) (100 . "AcDbLine") (10 6541.2509276018
2313.2738461538 0.0) (11 6568.6276809955 2313.2738461538 0.0))
((0 . "LINE") (100 . "AcDbEntity") (8 . "MASONRY") (62 . 7) (370 . 13) (100 . "AcDbLine") (10 6568.6276809955
2313.2738461538 0.0) (11 6602.5643325792 2313.2738461538 0.0))
((0 . "LINE") (100 . "AcDbEntity") (8 . "MASONRY") (62 . 7) (370 . 13) (100 . "AcDbLine") (10 6534.6910294118
2385.0702488688 0.0) (11 6770.358540724 2385.0702488688 0.0))
((0 . "LINE") (100 . "AcDbEntity") (8 . "MASONRY") (62 . 7) (370 . 13) (100 . "AcDbLine") (10 6770.358540724
2385.0702488688 0.0) (11 6770.358540724 2417.0439705882 0.0))
((0 . "LINE") (100 . "AcDbEntity") (8 . "MASONRY") (62 . 7) (370 . 13) (100 . "AcDbLine") (10 6602.5643325792
2273.7556561086 0.0) (11 6541.2509276018 2273.7556561086 0.0))
((0 . "LINE") (100 . "AcDbEntity") (8 . "MASONRY") (62 . 7) (370 . 13) (100 . "AcDbLine") (10 6541.2509276018
2273.7556561086 0.0) (11 6534.6910294118 2273.7556561086 0.0))
((0 . "LINE") (100 . "AcDbEntity") (8 . "MASONRY") (62 . 7) (370 . 13) (100 . "AcDbLine") (10 6677.9786538462
1134.9915384615 0.0) (11 6664.0938461538 1134.9915384615 0.0))
((0 . "LINE") (100 . "AcDbEntity") (8 . "MASONRY") (62 . 7) (370 . 13) (100 . "AcDbLine") (10 6664.0938461538
1134.9915384615 0.0) (11 6620.4972058824 1134.9915384615 0.0))
((0 . "LINE") (100 . "AcDbEntity") (8 . "MASONRY") (62 . 7) (370 . 13) (100 . "AcDbLine") (10 6549.7737556561
2337.8584502262 0.0) (11 6549.7737556561 2349.1706674208 0.0))
((0 . "LINE") (100 . "AcDbEntity") (8 . "MASONRY") (62 . 7) (370 . 13) (100 . "AcDbLine") (10 6595.0226244344
1155.0861877828 0.0) (11 6576.8287669683 1155.0861877828 0.0))
((0 . "LINE") (100 . "AcDbEntity") (8 . "MASONRY") (62 . 7) (370 . 13) (100 . "AcDbLine") (10 6602.5643325792
2273.7556561086 0.0) (11 6602.5643325792 2313.2738461538 0.0))
((0 . "LINE") (100 . "AcDbEntity") (8 . "MASONRY") (62 . 7) (370 . 13) (100 . "AcDbLine") (10 6602.5643325792
2313.2738461538 0.0) (11 6821.2635180995 2313.2738461538 0.0))
((0 . "LINE") (100 . "AcDbEntity") (8 . "MASONRY") (62 . 7) (370 . 13) (100 . "AcDbLine") (10 6821.2635180995
2313.2738461538 0.0) (11 6821.2635180995 2330.3167420814 0.0))
((0 . "LINE") (100 . "AcDbEntity") (8 . "MASONRY") (62 . 7) (370 . 13) (100 . "AcDbLine") (10 6783.5598076923
2273.7556561086 0.0) (11 6602.5643325792 2273.7556561086 0.0))
((0 . "LINE") (100 . "AcDbEntity") (8 . "MASONRY") (62 . 7) (370 . 13) (100 . "AcDbLine") (10 6687.4052714932
1907.9941968326 0.0) (11 6602.5643325792 1907.9941968326 0.0))
((0 . "LINE") (100 . "AcDbEntity") (8 . "MASONRY") (62 . 7) (370 . 13) (100 . "AcDbLine") (10 6689.2908710407
1672.3232352941 0.0) (11 6602.5643325792 1672.3232352941 0.0))
((0 . "LINE") (100 . "AcDbEntity") (8 . "MASONRY") (62 . 7) (370 . 13) (100 . "AcDbLine") (10 6606.334841629
2222.2486085973 0.0) (11 6642.1536425339 2222.2486085973 0.0))
((0 . "LINE") (100 . "AcDbEntity") (8 . "MASONRY") (62 . 7) (370 . 13) (100 . "AcDbLine") (10 6642.1536425339
2222.2486085973 0.0) (11 6642.1536425339 2202.1118438914 0.0))
((0 . "LINE") (100 . "AcDbEntity") (8 . "MASONRY") (62 . 7) (370 . 13) (100 . "AcDbLine") (10 6606.334841629
1742.0814479638 0.0) (11 6700.6065384615 1742.0814479638 0.0))
((0 . "LINE") (100 . "AcDbEntity") (8 . "MASONRY") (62 . 7) (370 . 13) (100 . "AcDbLine") (10 6606.334841629
1266.9683257919 0.0) (11 6647.8132013575 1266.9683257919 0.0))
((0 . "LINE") (100 . "AcDbEntity") (8 . "MASONRY") (62 . 7) (370 . 13) (100 . "AcDbLine") (10 6625.1887669683
1138.7627375566 0.0) (11 6606.334841629 1138.7627375566 0.0))
((0 . "LINE") (100 . "AcDbEntity") (8 . "MASONRY") (62 . 7) (370 . 13) (100 . "AcDbLine") (10 6610.1053506787
2104.07239819 0.0) (11 6651.5837104072 2104.07239819 0.0))
((0 . "LINE") (100 . "AcDbEntity") (8 . "MASONRY") (62 . 7) (370 . 13) (100 . "AcDbLine") (10 6875.9424547511
1987.1797171946 0.0) (11 6691.1025904977 1987.1797171946 0.0))
((0 . "LINE") (100 . "AcDbEntity") (8 . "MASONRY") (62 . 7) (370 . 13) (100 . "AcDbLine") (10 6691.1025904977
1987.1797171946 0.0) (11 6691.1025904977 2024.2875678733 0.0))
((0 . "LINE") (100 . "AcDbEntity") (8 . "MASONRY") (62 . 7) (370 . 13) (100 . "AcDbLine") (10 6691.1025904977
2024.2875678733 0.0) (11 6610.1053506787 2024.2875678733 0.0))
((0 . "LINE") (100 . "AcDbEntity") (8 . "MASONRY") (62 . 7) (370 . 13) (100 . "AcDbLine") (10 6700.6030882353
1432.8817647059 0.0) (11 6610.1053506787 1432.8817647059 0.0))
((0 . "LINE") (100 . "AcDbEntity") (8 . "MASONRY") (62 . 7) (370 . 13) (100 . "AcDbLine") (10 6783.5598076923
1336.7265384615 0.0) (11 6610.1053506787 1336.7265384615 0.0))
((0 . "LINE") (100 . "AcDbEntity") (8 . "MASONRY") (62 . 7) (370 . 13) (100 . "AcDbLine") (10 6628.8370701357
531.6141402715 0.0) (11 6644.0420022624 531.6141402715 0.0))
((0 . "LINE") (100 . "AcDbEntity") (8 . "MASONRY") (62 . 7) (370 . 13) (100 . "AcDbLine") (10 6645.92760181
2635.7466063348 0.0) (11 6645.92760181 2662.1415497738 0.0))
((0 . "LINE") (100 . "AcDbEntity") (8 . "MASONRY") (62 . 7) (370 . 13) (100 . "AcDbLine") (10 6649.6981108597
2573.5294117647 0.0) (11 6649.6981108597 2533.9366515837 0.0))
((0 . "LINE") (100 . "AcDbEntity") (8 . "MASONRY") (62 . 7) (370 . 13) (100 . "AcDbLine") (10 6649.6981108597
2573.5294117647 0.0) (11 6794.8720248869 2573.5294117647 0.0))
((0 . "LINE") (100 . "AcDbEntity") (8 . "MASONRY") (62 . 7) (370 . 13) (100 . "AcDbLine") (10 6644.0420022624
1591.2528054299 0.0) (11 6644.0420022624 1583.7104072398 0.0))
((0 . "LINE") (100 . "AcDbEntity") (8 . "MASONRY") (62 . 7) (370 . 13) (100 . "AcDbLine") (10 6645.92760181
2635.7466063348 0.0) (11 6907.9941968326 2635.7466063348 0.0))
((0 . "LINE") (100 . "AcDbEntity") (8 . "MASONRY") (62 . 7) (370 . 13) (100 . "AcDbLine") (10 6651.5837104072
2115.3846153846 0.0) (11 6651.5837104072 2104.07239819 0.0))
((0 . "LINE") (100 . "AcDbEntity") (8 . "MASONRY") (62 . 7) (370 . 13) (100 . "AcDbLine") (10 6659.125418552
2104.07239819 0.0) (11 6651.5837104072 2104.07239819 0.0))
((0 . "LINE") (100 . "AcDbEntity") (8 . "MASONRY") (62 . 7) (370 . 13) (100 . "AcDbLine") (10 6659.125418552
2156.8629751131 0.0) (11 6815.6108597285 2156.8629751131 0.0))
((0 . "LINE") (100 . "AcDbEntity") (8 . "MASONRY") (62 . 7) (370 . 13) (100 . "AcDbLine") (10 6700.6030882353
1291.4790497738 0.0) (11 6666.6664366516 1291.4790497738 0.0))
((0 . "LINE") (100 . "AcDbEntity") (8 . "MASONRY") (62 . 7) (370 . 13) (100 . "AcDbLine") (10 6670.4376357466
1257.467138009 0.0) (11 7023.0019683258 1257.467138009 0.0))
((0 . "LINE") (100 . "AcDbEntity") (8 . "MASONRY") (62 . 7) (370 . 13) (100 . "AcDbLine") (10 6687.4052714932
1900.4524886878 0.0) (11 6687.4052714932 1907.9941968326 0.0))
((0 . "LINE") (100 . "AcDbEntity") (8 . "MASONRY") (62 . 7) (370 . 13) (100 . "AcDbLine") (10 6687.4052714932
1907.9941968326 0.0) (11 6813.725260181 1907.9941968326 0.0))
((0 . "LINE") (100 . "AcDbEntity") (8 . "MASONRY") (62 . 7) (370 . 13) (100 . "AcDbLine") (10 6691.1764705882
1877.8280542986 0.0) (11 6691.1764705882 1858.9741289593 0.0))
((0 . "LINE") (100 . "AcDbEntity") (8 . "MASONRY") (62 . 7) (370 . 13) (100 . "AcDbLine") (10 6694.946979638
1553.5435746606 0.0) (11 6694.946979638 1572.3981900452 0.0))
((0 . "LINE") (100 . "AcDbEntity") (8 . "MASONRY") (62 . 7) (370 . 13) (100 . "AcDbLine") (10 6832.5791855204
727.7496493213 0.0) (11 6742.0814479638 727.7496493213 0.0))
((0 . "LINE") (100 . "AcDbEntity") (8 . "MASONRY") (62 . 7) (370 . 13) (100 . "AcDbLine") (10 6700.6065384615
1742.0814479638 0.0) (11 6836.3496945701 1742.0814479638 0.0))
((0 . "LINE") (100 . "AcDbEntity") (8 . "MASONRY") (62 . 7) (370 . 13) (100 . "AcDbLine") (10 6868.4007466063
1813.7245701357 0.0) (11 6700.6065384615 1813.7245701357 0.0))
((0 . "LINE") (100 . "AcDbEntity") (8 . "MASONRY") (62 . 7) (370 . 13) (100 . "AcDbLine") (10 6700.6065384615
1813.7245701357 0.0) (11 6700.6065384615 1742.0814479638 0.0))
((0 . "LINE") (100 . "AcDbEntity") (8 . "MASONRY") (62 . 7) (370 . 13) (100 . "AcDbLine") (10 6700.6030882353
1538.387658371 0.0) (11 6836.3496945701 1538.387658371 0.0))
((0 . "LINE") (100 . "AcDbEntity") (8 . "MASONRY") (62 . 7) (370 . 13) (100 . "AcDbLine") (10 6836.3496945701
1538.387658371 0.0) (11 6862.7453280543 1538.387658371 0.0))
((0 . "LINE") (100 . "AcDbEntity") (8 . "MASONRY") (62 . 7) (370 . 13) (100 . "AcDbLine") (10 6862.7453280543
1538.387658371 0.0) (11 7028.6573868778 1538.387658371 0.0))
((0 . "LINE") (100 . "AcDbEntity") (8 . "MASONRY") (62 . 7) (370 . 13) (100 . "AcDbLine") (10 6700.6030882353
1432.8817647059 0.0) (11 6700.6030882353 1459.2760180995 0.0))
((0 . "LINE") (100 . "AcDbEntity") (8 . "MASONRY") (62 . 7) (370 . 13) (100 . "AcDbLine") (10 6700.6030882353
1432.8817647059 0.0) (11 6821.2669683258 1432.8817647059 0.0))
((0 . "LINE") (100 . "AcDbEntity") (8 . "MASONRY") (62 . 7) (370 . 13) (100 . "AcDbLine") (10 6704.3742873303
2104.07239819 0.0) (11 6772.2475904977 2104.07239819 0.0))
((0 . "LINE") (100 . "AcDbEntity") (8 . "MASONRY") (62 . 7) (370 . 13) (100 . "AcDbLine") (10 6779.7886085973
1031.2980542986 0.0) (11 6708.1447963801 1031.2980542986 0.0))
((0 . "LINE") (100 . "AcDbEntity") (8 . "MASONRY") (62 . 7) (370 . 13) (100 . "AcDbLine") (10 6832.5791855204
835.2191628959 0.0) (11 6742.0814479638 835.2191628959 0.0))
((0 . "LINE") (100 . "AcDbEntity") (8 . "MASONRY") (62 . 7) (370 . 13) (100 . "AcDbLine") (10 6826.9230769231
1093.437918552 0.0) (11 6734.539739819 1093.437918552 0.0))
((0 . "LINE") (100 . "AcDbEntity") (8 . "MASONRY") (62 . 7) (370 . 13) (100 . "AcDbLine") (10 6734.539739819
1093.437918552 0.0) (11 6719.4570135747 1093.437918552 0.0))
((0 . "LINE") (100 . "AcDbEntity") (8 . "MASONRY") (62 . 7) (370 . 13) (100 . "AcDbLine") (10 6819.3820588235
1165.1583710407 0.0) (11 6730.7692307692 1165.1583710407 0.0))
((0 . "LINE") (100 . "AcDbEntity") (8 . "MASONRY") (62 . 7) (370 . 13) (100 . "AcDbLine") (10 6855.2036199095
776.7635067873 0.0) (11 6742.0814479638 776.7635067873 0.0))
((0 . "LINE") (100 . "AcDbEntity") (8 . "MASONRY") (62 . 7) (370 . 13) (100 . "AcDbLine") (10 6853.4664705882
2786.575938914 0.0) (11 6853.4664705882 2757.1471945701 0.0))
((0 . "LINE") (100 . "AcDbEntity") (8 . "MASONRY") (62 . 7) (370 . 13) (100 . "AcDbLine") (10 6853.4664705882
2757.1471945701 0.0) (11 6821.2669683258 2757.1471945701 0.0))
((0 . "LINE") (100 . "AcDbEntity") (8 . "MASONRY") (62 . 7) (370 . 13) (100 . "AcDbLine") (10 6772.853800905
464.2503846154 0.0) (11 6772.853800905 484.5728846154 0.0))
((0 . "LINE") (100 . "AcDbEntity") (8 . "MASONRY") (62 . 7) (370 . 13) (100 . "AcDbLine") (10 6772.853800905
484.5728846154 0.0) (11 6738.60989819 484.5728846154 0.0))
((0 . "LINE") (100 . "AcDbEntity") (8 . "MASONRY") (62 . 7) (370 . 13) (100 . "AcDbLine") (10 6815.5335294118
1334.8416289593 0.0) (11 6815.5335294118 1367.343540724 0.0))
((0 . "LINE") (100 . "AcDbEntity") (8 . "MASONRY") (62 . 7) (370 . 13) (100 . "AcDbLine") (10 6815.5335294118
1367.343540724 0.0) (11 6751.5080656109 1367.343540724 0.0))
((0 . "LINE") (100 . "AcDbEntity") (8 . "MASONRY") (62 . 7) (370 . 13) (100 . "AcDbLine") (10 6751.5080656109
1367.343540724 0.0) (11 6751.5080656109 1395.1725339367 0.0))
((0 . "LINE") (100 . "AcDbEntity") (8 . "MASONRY") (62 . 7) (370 . 13) (100 . "AcDbLine") (10 6753.3936651584
1670.4383257919 0.0) (11 6783.5598076923 1670.4383257919 0.0))
((0 . "LINE") (100 . "AcDbEntity") (8 . "MASONRY") (62 . 7) (370 . 13) (100 . "AcDbLine") (10 6753.3936651584
1466.8184162896 0.0) (11 6772.2475904977 1466.8184162896 0.0))
((0 . "LINE") (100 . "AcDbEntity") (8 . "MASONRY") (62 . 7) (370 . 13) (100 . "AcDbLine") (10 6760.9353733032
599.5475113122 0.0) (11 6760.9353733032 539.2166063348 0.0))
((0 . "LINE") (100 . "AcDbEntity") (8 . "MASONRY") (62 . 7) (370 . 13) (100 . "AcDbLine") (10 6866.5158371041
2818.701561086 0.0) (11 6821.2669683258 2818.701561086 0.0))
((0 . "LINE") (100 . "AcDbEntity") (8 . "MASONRY") (62 . 7) (370 . 13) (100 . "AcDbLine") (10 6826.9230769231
1025.6419457014 0.0) (11 6802.4130429864 1025.6419457014 0.0))
((0 . "LINE") (100 . "AcDbEntity") (8 . "MASONRY") (62 . 7) (370 . 13) (100 . "AcDbLine") (10 7139.893959276
2271.8707466063 0.0) (11 6960.7840837104 2271.8707466063 0.0))
((0 . "LINE") (100 . "AcDbEntity") (8 . "MASONRY") (62 . 7) (370 . 13) (100 . "AcDbLine") (10 6960.7840837104
2271.8707466063 0.0) (11 6809.9547511312 2271.8707466063 0.0))
((0 . "LINE") (100 . "AcDbEntity") (8 . "MASONRY") (62 . 7) (370 . 13) (100 . "AcDbLine") (10 6815.6108597285
2156.8629751131 0.0) (11 6815.6108597285 2111.6141063348 0.0))
((0 . "LINE") (100 . "AcDbEntity") (8 . "MASONRY") (62 . 7) (370 . 13) (100 . "AcDbLine") (10 6815.6108597285
2156.8629751131 0.0) (11 7015.460260181 2156.8629751131 0.0))
((0 . "LINE") (100 . "AcDbEntity") (8 . "MASONRY") (62 . 7) (370 . 13) (100 . "AcDbLine") (10 7015.460260181
2156.8629751131 0.0) (11 7015.460260181 2188.9140271493 0.0))
((0 . "LINE") (100 . "AcDbEntity") (8 . "MASONRY") (62 . 7) (370 . 13) (100 . "AcDbLine") (10 6821.2669683258
1466.8184162896 0.0) (11 6821.2669683258 1432.8817647059 0.0))
((0 . "LINE") (100 . "AcDbEntity") (8 . "MASONRY") (62 . 7) (370 . 13) (100 . "AcDbLine") (10 6819.3820588235
1146.3037556561 0.0) (11 6819.3820588235 1165.1583710407 0.0))
((0 . "LINE") (100 . "AcDbEntity") (8 . "MASONRY") (62 . 7) (370 . 13) (100 . "AcDbLine") (10 6950.0739366516
1165.1583710407 0.0) (11 6819.3820588235 1165.1583710407 0.0))
((0 . "LINE") (100 . "AcDbEntity") (8 . "MASONRY") (62 . 7) (370 . 13) (100 . "AcDbLine") (10 6983.4085180995
3184.3891402715 0.0) (11 6821.2669683258 3184.3891402715 0.0))
((0 . "LINE") (100 . "AcDbEntity") (8 . "MASONRY") (62 . 7) (370 . 13) (100 . "AcDbLine") (10 6821.2669683258
3114.6302375566 0.0) (11 6885.3697624434 3114.6302375566 0.0))
((0 . "LINE") (100 . "AcDbEntity") (8 . "MASONRY") (62 . 7) (370 . 13) (100 . "AcDbLine") (10 6821.2669683258
1410.2573303167 0.0) (11 6821.2669683258 1432.8817647059 0.0))
((0 . "LINE") (100 . "AcDbEntity") (8 . "MASONRY") (62 . 7) (370 . 13) (100 . "AcDbLine") (10 6821.2669683258
584.4654751131 0.0) (11 6945.7013574661 584.4654751131 0.0))
((0 . "LINE") (100 . "AcDbEntity") (8 . "MASONRY") (62 . 7) (370 . 13) (100 . "AcDbLine") (10 6825.0374773756
2899.8113461538 0.0) (11 6857.1175226244 2899.8113461538 0.0))
((0 . "LINE") (100 . "AcDbEntity") (8 . "MASONRY") (62 . 7) (370 . 13) (100 . "AcDbLine") (10 6857.1175226244
2899.8113461538 0.0) (11 6857.1175226244 2907.2398190045 0.0))
((0 . "LINE") (100 . "AcDbEntity") (8 . "MASONRY") (62 . 7) (370 . 13) (100 . "AcDbLine") (10 6830.6935859729
2345.3994683258 0.0) (11 6830.6935859729 2424.5849886878 0.0))
((0 . "LINE") (100 . "AcDbEntity") (8 . "MASONRY") (62 . 7) (370 . 13) (100 . "AcDbLine") (10 6826.9230769231
1025.6419457014 0.0) (11 6826.9230769231 1093.437918552 0.0))
((0 . "LINE") (100 . "AcDbEntity") (8 . "MASONRY") (62 . 7) (370 . 13) (100 . "AcDbLine") (10 6826.9230769231
1093.437918552 0.0) (11 6911.7647058824 1093.437918552 0.0))
((0 . "LINE") (100 . "AcDbEntity") (8 . "MASONRY") (62 . 7) (370 . 13) (100 . "AcDbLine") (10 7209.652861991
2973.2282126697 0.0) (11 6828.8086764706 2973.2282126697 0.0))
((0 . "LINE") (100 . "AcDbEntity") (8 . "MASONRY") (62 . 7) (370 . 13) (100 . "AcDbLine") (10 6826.9230769231
1025.6419457014 0.0) (11 6836.3496945701 1025.6419457014 0.0))
((0 . "LINE") (100 . "AcDbEntity") (8 . "MASONRY") (62 . 7) (370 . 13) (100 . "AcDbLine") (10 6832.5791855204
2471.7967873303 0.0) (11 6852.7898303167 2471.7967873303 0.0))
((0 . "LINE") (100 . "AcDbEntity") (8 . "MASONRY") (62 . 7) (370 . 13) (100 . "AcDbLine") (10 6852.7898303167
2471.7967873303 0.0) (11 6852.7898303167 2498.037760181 0.0))
((0 . "LINE") (100 . "AcDbEntity") (8 . "MASONRY") (62 . 7) (370 . 13) (100 . "AcDbLine") (10 6834.4640950226
965.308280543 0.0) (11 6834.4640950226 984.1628959276 0.0))
((0 . "LINE") (100 . "AcDbEntity") (8 . "MASONRY") (62 . 7) (370 . 13) (100 . "AcDbLine") (10 6832.5791855204
863.4983257919 0.0) (11 6832.5791855204 835.2191628959 0.0))
((0 . "LINE") (100 . "AcDbEntity") (8 . "MASONRY") (62 . 7) (370 . 13) (100 . "AcDbLine") (10 6832.5791855204
835.2191628959 0.0) (11 7036.5677941176 835.2191628959 0.0))
((0 . "LINE") (100 . "AcDbEntity") (8 . "MASONRY") (62 . 7) (370 . 13) (100 . "AcDbLine") (10 6832.5791855204
727.7496493213 0.0) (11 6832.5791855204 686.2754298643 0.0))
((0 . "LINE") (100 . "AcDbEntity") (8 . "MASONRY") (62 . 7) (370 . 13) (100 . "AcDbLine") (10 6832.5791855204
727.7496493213 0.0) (11 6907.9941968326 727.7496493213 0.0))
((0 . "LINE") (100 . "AcDbEntity") (8 . "MASONRY") (62 . 7) (370 . 13) (100 . "AcDbLine") (10 6836.3496945701
1776.0180995475 0.0) (11 6836.3496945701 1742.0814479638 0.0))
((0 . "LINE") (100 . "AcDbEntity") (8 . "MASONRY") (62 . 7) (370 . 13) (100 . "AcDbLine") (10 7024.8868778281
1742.0814479638 0.0) (11 6885.3697624434 1742.0814479638 0.0))
((0 . "LINE") (100 . "AcDbEntity") (8 . "MASONRY") (62 . 7) (370 . 13) (100 . "AcDbLine") (10 6885.3697624434
1742.0814479638 0.0) (11 6836.3496945701 1742.0814479638 0.0))
((0 . "LINE") (100 . "AcDbEntity") (8 . "MASONRY") (62 . 7) (370 . 13) (100 . "AcDbLine") (10 6847.6619117647
3525.6412556561 0.0) (11 6972.096300905 3525.6412556561 0.0))
((0 . "LINE") (100 . "AcDbEntity") (8 . "MASONRY") (62 . 7) (370 . 13) (100 . "AcDbLine") (10 7175.7162104072
3257.9185520362 0.0) (11 6847.6619117647 3257.9185520362 0.0))
((0 . "LINE") (100 . "AcDbEntity") (8 . "MASONRY") (62 . 7) (370 . 13) (100 . "AcDbLine") (10 6853.3187104072
3427.6018099548 0.0) (11 6853.3187104072 3382.3529411765 0.0))
((0 . "LINE") (100 . "AcDbEntity") (8 . "MASONRY") (62 . 7) (370 . 13) (100 . "AcDbLine") (10 6857.0926696833
3450.2262443439 0.0) (11 6857.0926696833 3470.9657692308 0.0))
((0 . "LINE") (100 . "AcDbEntity") (8 . "MASONRY") (62 . 7) (370 . 13) (100 . "AcDbLine") (10 6857.0926696833
3470.9657692308 0.0) (11 6972.096300905 3470.9657692308 0.0))
((0 . "LINE") (100 . "AcDbEntity") (8 . "MASONRY") (62 . 7) (370 . 13) (100 . "AcDbLine") (10 6852.7898303167
2498.037760181 0.0) (11 7149.3212669683 2498.037760181 0.0))
((0 . "LINE") (100 . "AcDbEntity") (8 . "MASONRY") (62 . 7) (370 . 13) (100 . "AcDbLine") (10 7149.3212669683
2498.037760181 0.0) (11 7228.5067873303 2498.037760181 0.0))
((0 . "LINE") (100 . "AcDbEntity") (8 . "MASONRY") (62 . 7) (370 . 13) (100 . "AcDbLine") (10 6945.7013574661
3341.0292420814 0.0) (11 6870.2863461538 3341.0292420814 0.0))
((0 . "LINE") (100 . "AcDbEntity") (8 . "MASONRY") (62 . 7) (370 . 13) (100 . "AcDbLine") (10 6870.2863461538
3341.0292420814 0.0) (11 6858.9741289593 3341.0292420814 0.0))
((0 . "LINE") (100 . "AcDbEntity") (8 . "MASONRY") (62 . 7) (370 . 13) (100 . "AcDbLine") (10 6862.7453280543
1674.1308144796 0.0) (11 6877.8280542986 1674.1308144796 0.0))
((0 . "LINE") (100 . "AcDbEntity") (8 . "MASONRY") (62 . 7) (370 . 13) (100 . "AcDbLine") (10 6877.8280542986
1674.1308144796 0.0) (11 7017.3451696833 1674.1308144796 0.0))
((0 . "LINE") (100 . "AcDbEntity") (8 . "MASONRY") (62 . 7) (370 . 13) (100 . "AcDbLine") (10 6866.5158371041
2818.701561086 0.0) (11 6866.5158371041 2865.761459276 0.0))
((0 . "LINE") (100 . "AcDbEntity") (8 . "MASONRY") (62 . 7) (370 . 13) (100 . "AcDbLine") (10 6866.5158371041
2818.701561086 0.0) (11 7175.7162104072 2818.701561086 0.0))
((0 . "LINE") (100 . "AcDbEntity") (8 . "MASONRY") (62 . 7) (370 . 13) (100 . "AcDbLine") (10 7175.7162104072
2818.701561086 0.0) (11 7213.346040724 2818.701561086 0.0))
((0 . "LINE") (100 . "AcDbEntity") (8 . "MASONRY") (62 . 7) (370 . 13) (100 . "AcDbLine") (10 7213.346040724
2818.701561086 0.0) (11 7213.346040724 2865.761459276 0.0))
((0 . "LINE") (100 . "AcDbEntity") (8 . "MASONRY") (62 . 7) (370 . 13) (100 . "AcDbLine") (10 6896.681979638
1813.7245701357 0.0) (11 6868.4007466063 1813.7245701357 0.0))
((0 . "LINE") (100 . "AcDbEntity") (8 . "MASONRY") (62 . 7) (370 . 13) (100 . "AcDbLine") (10 6868.4007466063
1828.8086764706 0.0) (11 6868.4007466063 1813.7245701357 0.0))
((0 . "LINE") (100 . "AcDbEntity") (8 . "MASONRY") (62 . 7) (370 . 13) (100 . "AcDbLine") (10 7038.0840045249
1334.8416289593 0.0) (11 6866.5158371041 1334.8416289593 0.0))
((0 . "LINE") (100 . "AcDbEntity") (8 . "MASONRY") (62 . 7) (370 . 13) (100 . "AcDbLine") (10 6875.9424547511
1987.1797171946 0.0) (11 7013.5746606335 1987.1797171946 0.0))
((0 . "LINE") (100 . "AcDbEntity") (8 . "MASONRY") (62 . 7) (370 . 13) (100 . "AcDbLine") (10 6875.9424547511
1987.1797171946 0.0) (11 6875.9424547511 2021.0390384615 0.0))
((0 . "LINE") (100 . "AcDbEntity") (8 . "MASONRY") (62 . 7) (370 . 13) (100 . "AcDbLine") (10 6875.9424547511
2021.0390384615 0.0) (11 7013.5746606335 2021.0390384615 0.0))
((0 . "LINE") (100 . "AcDbEntity") (8 . "MASONRY") (62 . 7) (370 . 13) (100 . "AcDbLine") (10 6923.0769230769
1921.1878733032 0.0) (11 6870.8145361991 1921.1878733032 0.0))
((0 . "LINE") (100 . "AcDbEntity") (8 . "MASONRY") (62 . 7) (370 . 13) (100 . "AcDbLine") (10 6870.8145361991
1921.1878733032 0.0) (11 6870.8145361991 1840.1208936652 0.0))
((0 . "LINE") (100 . "AcDbEntity") (8 . "MASONRY") (62 . 7) (370 . 13) (100 . "AcDbLine") (10 6874.0609954751
1414.0271493213 0.0) (11 6874.0609954751 1451.7336199095 0.0))
((0 . "LINE") (100 . "AcDbEntity") (8 . "MASONRY") (62 . 7) (370 . 13) (100 . "AcDbLine") (10 6874.0609954751
1451.7336199095 0.0) (11 7028.6573868778 1451.7336199095 0.0))
((0 . "LINE") (100 . "AcDbEntity") (8 . "MASONRY") (62 . 7) (370 . 13) (100 . "AcDbLine") (10 7028.6573868778
1451.7336199095 0.0) (11 7055.0523303167 1451.7336199095 0.0))
((0 . "LINE") (100 . "AcDbEntity") (8 . "MASONRY") (62 . 7) (370 . 13) (100 . "AcDbLine") (10 6870.2863461538
648.566199095 0.0) (11 6907.9941968326 648.566199095 0.0))
((0 . "LINE") (100 . "AcDbEntity") (8 . "MASONRY") (62 . 7) (370 . 13) (100 . "AcDbLine") (10 6881.5985633484
2748.8687782805 0.0) (11 7051.281821267 2748.8687782805 0.0))
((0 . "LINE") (100 . "AcDbEntity") (8 . "MASONRY") (62 . 7) (370 . 13) (100 . "AcDbLine") (10 6900.4524886878
1019.9844570136 0.0) (11 6881.5985633484 1019.9844570136 0.0))
((0 . "LINE") (100 . "AcDbEntity") (8 . "MASONRY") (62 . 7) (370 . 13) (100 . "AcDbLine") (10 6895.6946493213
506.1395588235 0.0) (11 6895.6946493213 520.3619909502 0.0))
((0 . "LINE") (100 . "AcDbEntity") (8 . "MASONRY") (62 . 7) (370 . 13) (100 . "AcDbLine") (10 6915.5352149321
3122.1719457014 0.0) (11 6915.5352149321 3095.7770022624 0.0))
((0 . "LINE") (100 . "AcDbEntity") (8 . "MASONRY") (62 . 7) (370 . 13) (100 . "AcDbLine") (10 6907.9941968326
2647.0588235294 0.0) (11 6907.9941968326 2635.7466063348 0.0))
((0 . "LINE") (100 . "AcDbEntity") (8 . "MASONRY") (62 . 7) (370 . 13) (100 . "AcDbLine") (10 6960.7840837104
2635.7466063348 0.0) (11 6907.9941968326 2635.7466063348 0.0))
((0 . "LINE") (100 . "AcDbEntity") (8 . "MASONRY") (62 . 7) (370 . 13) (100 . "AcDbLine") (10 7024.8868778281
2903.4693099548 0.0) (11 6911.7647058824 2903.4693099548 0.0))
((0 . "LINE") (100 . "AcDbEntity") (8 . "MASONRY") (62 . 7) (370 . 13) (100 . "AcDbLine") (10 6987.1797171946
1806.1849321267 0.0) (11 6911.7647058824 1806.1849321267 0.0))
((0 . "LINE") (100 . "AcDbEntity") (8 . "MASONRY") (62 . 7) (370 . 13) (100 . "AcDbLine") (10 6983.4085180995
784.3141855204 0.0) (11 6911.7647058824 784.3141855204 0.0))
((0 . "LINE") (100 . "AcDbEntity") (8 . "MASONRY") (62 . 7) (370 . 13) (100 . "AcDbLine") (10 6923.0769230769
2567.8733031674 0.0) (11 6923.0769230769 2556.5610859729 0.0))
((0 . "LINE") (100 . "AcDbEntity") (8 . "MASONRY") (62 . 7) (370 . 13) (100 . "AcDbLine") (10 6930.6179411765
3054.2986425339 0.0) (11 6930.6179411765 3024.1325 0.0))
((0 . "LINE") (100 . "AcDbEntity") (8 . "MASONRY") (62 . 7) (370 . 13) (100 . "AcDbLine") (10 6938.1596493213
2188.9140271493 0.0) (11 7015.460260181 2188.9140271493 0.0))
((0 . "LINE") (100 . "AcDbEntity") (8 . "MASONRY") (62 . 7) (370 . 13) (100 . "AcDbLine") (10 6950.0739366516
1165.1583710407 0.0) (11 6950.0739366516 1108.5972850679 0.0))
((0 . "LINE") (100 . "AcDbEntity") (8 . "MASONRY") (62 . 7) (370 . 13) (100 . "AcDbLine") (10 6950.0739366516
1108.5972850679 0.0) (11 6975.8668099548 1108.5972850679 0.0))
((0 . "LINE") (100 . "AcDbEntity") (8 . "MASONRY") (62 . 7) (370 . 13) (100 . "AcDbLine") (10 6950.0739366516
1165.1583710407 0.0) (11 7013.5746606335 1165.1583710407 0.0))
((0 . "LINE") (100 . "AcDbEntity") (8 . "MASONRY") (62 . 7) (370 . 13) (100 . "AcDbLine") (10 6953.2430656109
2552.7905769231 0.0) (11 6972.096300905 2552.7905769231 0.0))
((0 . "LINE") (100 . "AcDbEntity") (8 . "MASONRY") (62 . 7) (370 . 13) (100 . "AcDbLine") (10 6964.5552828054
3340.874581448 0.0) (11 6957.0135746606 3340.874581448 0.0))
((0 . "LINE") (100 . "AcDbEntity") (8 . "MASONRY") (62 . 7) (370 . 13) (100 . "AcDbLine") (10 7055.053020362
2635.7466063348 0.0) (11 7032.4285859729 2635.7466063348 0.0))
((0 . "LINE") (100 . "AcDbEntity") (8 . "MASONRY") (62 . 7) (370 . 13) (100 . "AcDbLine") (10 7032.4285859729
2635.7466063348 0.0) (11 6987.1797171946 2635.7466063348 0.0))
((0 . "LINE") (100 . "AcDbEntity") (8 . "MASONRY") (62 . 7) (370 . 13) (100 . "AcDbLine") (10 6987.1797171946
2635.7466063348 0.0) (11 6983.4085180995 2635.7466063348 0.0))
((0 . "LINE") (100 . "AcDbEntity") (8 . "MASONRY") (62 . 7) (370 . 13) (100 . "AcDbLine") (10 6983.4085180995
2635.7466063348 0.0) (11 6960.7840837104 2635.7466063348 0.0))
((0 . "LINE") (100 . "AcDbEntity") (8 . "MASONRY") (62 . 7) (370 . 13) (100 . "AcDbLine") (10 6972.096300905
3525.6412556561 0.0) (11 6972.096300905 3514.3290384615 0.0))
((0 . "LINE") (100 . "AcDbEntity") (8 . "MASONRY") (62 . 7) (370 . 13) (100 . "AcDbLine") (10 6972.096300905
3536.9534728507 0.0) (11 6972.096300905 3525.6412556561 0.0))
((0 . "LINE") (100 . "AcDbEntity") (8 . "MASONRY") (62 . 7) (370 . 13) (100 . "AcDbLine") (10 7322.7750339367
3514.3290384615 0.0) (11 6972.096300905 3514.3290384615 0.0))
((0 . "LINE") (100 . "AcDbEntity") (8 . "MASONRY") (62 . 7) (370 . 13) (100 . "AcDbLine") (10 6972.096300905
3470.9657692308 0.0) (11 6972.096300905 3514.3290384615 0.0))
((0 . "LINE") (100 . "AcDbEntity") (8 . "MASONRY") (62 . 7) (370 . 13) (100 . "AcDbLine") (10 6972.096300905
3470.9657692308 0.0) (11 7322.7750339367 3470.9657692308 0.0))
((0 . "LINE") (100 . "AcDbEntity") (8 . "MASONRY") (62 . 7) (370 . 13) (100 . "AcDbLine") (10 7032.4285859729
3095.7763122172 0.0) (11 6972.096300905 3095.7763122172 0.0))
((0 . "LINE") (100 . "AcDbEntity") (8 . "MASONRY") (62 . 7) (370 . 13) (100 . "AcDbLine") (10 6987.1797171946
3014.7058823529 0.0) (11 6972.096300905 3014.7058823529 0.0))
((0 . "LINE") (100 . "AcDbEntity") (8 . "MASONRY") (62 . 7) (370 . 13) (100 . "AcDbLine") (10 6975.8668099548
1078.4304524887 0.0) (11 6975.8668099548 1108.5972850679 0.0))
((0 . "LINE") (100 . "AcDbEntity") (8 . "MASONRY") (62 . 7) (370 . 13) (100 . "AcDbLine") (10 6979.6380090498
2581.0704298643 0.0) (11 7141.7795588235 2581.0704298643 0.0))
((0 . "LINE") (100 . "AcDbEntity") (8 . "MASONRY") (62 . 7) (370 . 13) (100 . "AcDbLine") (10 6979.6380090498
1924.9618325792 0.0) (11 7088.9896719457 1924.9618325792 0.0))
((0 . "LINE") (100 . "AcDbEntity") (8 . "MASONRY") (62 . 7) (370 . 13) (100 . "AcDbLine") (10 7349.1706674208
1108.5972850679 0.0) (11 6975.8668099548 1108.5972850679 0.0))
((0 . "LINE") (100 . "AcDbEntity") (8 . "MASONRY") (62 . 7) (370 . 13) (100 . "AcDbLine") (10 6994.7207352941
3340.874581448 0.0) (11 6983.4085180995 3340.874581448 0.0))
((0 . "LINE") (100 . "AcDbEntity") (8 . "MASONRY") (62 . 7) (370 . 13) (100 . "AcDbLine") (10 6990.9502262443
1417.7969683258 0.0) (11 7055.0523303167 1417.7969683258 0.0))
((0 . "LINE") (100 . "AcDbEntity") (8 . "MASONRY") (62 . 7) (370 . 13) (100 . "AcDbLine") (10 6994.7207352941
3129.7136538462 0.0) (11 7028.6573868778 3129.7136538462 0.0))
((0 . "LINE") (100 . "AcDbEntity") (8 . "MASONRY") (62 . 7) (370 . 13) (100 . "AcDbLine") (10 7002.2624434389
1806.1849321267 0.0) (11 7024.8868778281 1806.1849321267 0.0))
((0 . "LINE") (100 . "AcDbEntity") (8 . "MASONRY") (62 . 7) (370 . 13) (100 . "AcDbLine") (10 7043.7408031674
2107.8435972851 0.0) (11 7006.0329524887 2107.8435972851 0.0))
((0 . "LINE") (100 . "AcDbEntity") (8 . "MASONRY") (62 . 7) (370 . 13) (100 . "AcDbLine") (10 7013.5746606335
1987.1797171946 0.0) (11 7013.5746606335 2021.0390384615 0.0))
((0 . "LINE") (100 . "AcDbEntity") (8 . "MASONRY") (62 . 7) (370 . 13) (100 . "AcDbLine") (10 7013.5746606335
2021.0390384615 0.0) (11 7013.5746606335 2077.6774547511 0.0))
((0 . "LINE") (100 . "AcDbEntity") (8 . "MASONRY") (62 . 7) (370 . 13) (100 . "AcDbLine") (10 7013.5746606335
1987.1797171946 0.0) (11 7173.831300905 1987.1797171946 0.0))
((0 . "LINE") (100 . "AcDbEntity") (8 . "MASONRY") (62 . 7) (370 . 13) (100 . "AcDbLine") (10 7119.1551244344
1674.1308144796 0.0) (11 7017.3451696833 1674.1308144796 0.0))
((0 . "LINE") (100 . "AcDbEntity") (8 . "MASONRY") (62 . 7) (370 . 13) (100 . "AcDbLine") (10 7017.3451696833
1576.1680090498 0.0) (11 7017.3451696833 1621.4168778281 0.0))
((0 . "LINE") (100 . "AcDbEntity") (8 . "MASONRY") (62 . 7) (370 . 13) (100 . "AcDbLine") (10 7017.3451696833
1621.4168778281 0.0) (11 7017.3451696833 1674.1308144796 0.0))
((0 . "LINE") (100 . "AcDbEntity") (8 . "MASONRY") (62 . 7) (370 . 13) (100 . "AcDbLine") (10 7473.6050565611
2188.9140271493 0.0) (11 7134.238540724 2188.9140271493 0.0))
((0 . "LINE") (100 . "AcDbEntity") (8 . "MASONRY") (62 . 7) (370 . 13) (100 . "AcDbLine") (10 7134.238540724
2188.9140271493 0.0) (11 7015.460260181 2188.9140271493 0.0))
((0 . "LINE") (100 . "AcDbEntity") (8 . "MASONRY") (62 . 7) (370 . 13) (100 . "AcDbLine") (10 7311.4628167421
1257.467138009 0.0) (11 7292.609581448 1257.467138009 0.0))
((0 . "LINE") (100 . "AcDbEntity") (8 . "MASONRY") (62 . 7) (370 . 13) (100 . "AcDbLine") (10 7292.609581448
1257.467138009 0.0) (11 7023.0019683258 1257.467138009 0.0))
((0 . "LINE") (100 . "AcDbEntity") (8 . "MASONRY") (62 . 7) (370 . 13) (100 . "AcDbLine") (10 7023.0019683258
1206.6374208145 0.0) (11 7023.0019683258 1257.467138009 0.0))
((0 . "LINE") (100 . "AcDbEntity") (8 . "MASONRY") (62 . 7) (370 . 13) (100 . "AcDbLine") (10 7024.8868778281
2903.4693099548 0.0) (11 7024.8868778281 2911.0103280543 0.0))
((0 . "LINE") (100 . "AcDbEntity") (8 . "MASONRY") (62 . 7) (370 . 13) (100 . "AcDbLine") (10 7024.8868778281
2903.4693099548 0.0) (11 7213.424061086 2903.4693099548 0.0))
((0 . "LINE") (100 . "AcDbEntity") (8 . "MASONRY") (62 . 7) (370 . 13) (100 . "AcDbLine") (10 7224.7362782805
2371.7212217195 0.0) (11 7039.9696040724 2371.7212217195 0.0))
((0 . "LINE") (100 . "AcDbEntity") (8 . "MASONRY") (62 . 7) (370 . 13) (100 . "AcDbLine") (10 7039.9696040724
2371.7212217195 0.0) (11 7024.8868778281 2371.7212217195 0.0))
((0 . "LINE") (100 . "AcDbEntity") (8 . "MASONRY") (62 . 7) (370 . 13) (100 . "AcDbLine") (10 7024.8868778281
1806.1849321267 0.0) (11 7024.8868778281 1742.0814479638 0.0))
((0 . "LINE") (100 . "AcDbEntity") (8 . "MASONRY") (62 . 7) (370 . 13) (100 . "AcDbLine") (10 7024.8868778281
1806.1849321267 0.0) (11 7300.1505995475 1806.1849321267 0.0))
((0 . "LINE") (100 . "AcDbEntity") (8 . "MASONRY") (62 . 7) (370 . 13) (100 . "AcDbLine") (10 7126.6968325792
1742.0814479638 0.0) (11 7024.8868778281 1742.0814479638 0.0))
((0 . "LINE") (100 . "AcDbEntity") (8 . "MASONRY") (62 . 7) (370 . 13) (100 . "AcDbLine") (10 7043.7408031674
3171.1913235294 0.0) (11 7043.7408031674 3191.930158371 0.0))
((0 . "LINE") (100 . "AcDbEntity") (8 . "MASONRY") (62 . 7) (370 . 13) (100 . "AcDbLine") (10 7073.9062556561
1451.7336199095 0.0) (11 7055.0523303167 1451.7336199095 0.0))
((0 . "LINE") (100 . "AcDbEntity") (8 . "MASONRY") (62 . 7) (370 . 13) (100 . "AcDbLine") (10 7051.281821267
3337.1040723982 0.0) (11 7036.1990950226 3337.1040723982 0.0))
((0 . "LINE") (100 . "AcDbEntity") (8 . "MASONRY") (62 . 7) (370 . 13) (100 . "AcDbLine") (10 7038.0840045249
1334.8416289593 0.0) (11 7038.0840045249 1300.9049773756 0.0))
((0 . "LINE") (100 . "AcDbEntity") (8 . "MASONRY") (62 . 7) (370 . 13) (100 . "AcDbLine") (10 7038.0840045249
1334.8416289593 0.0) (11 7175.7162104072 1334.8416289593 0.0))
((0 . "LINE") (100 . "AcDbEntity") (8 . "MASONRY") (62 . 7) (370 . 13) (100 . "AcDbLine") (10 7043.7408031674
835.2191628959 0.0) (11 7036.5677941176 835.2191628959 0.0))
((0 . "LINE") (100 . "AcDbEntity") (8 . "MASONRY") (62 . 7) (370 . 13) (100 . "AcDbLine") (10 7036.5677941176
835.2191628959 0.0) (11 7036.5677941176 903.0924660633 0.0))
((0 . "LINE") (100 . "AcDbEntity") (8 . "MASONRY") (62 . 7) (370 . 13) (100 . "AcDbLine") (10 7141.7795588235
989.709219457 0.0) (11 7036.5677941176 989.709219457 0.0))
((0 . "LINE") (100 . "AcDbEntity") (8 . "MASONRY") (62 . 7) (370 . 13) (100 . "AcDbLine") (10 7036.5677941176
989.709219457 0.0) (11 7036.5677941176 903.0924660633 0.0))
((0 . "LINE") (100 . "AcDbEntity") (8 . "MASONRY") (62 . 7) (370 . 13) (100 . "AcDbLine") (10 7122.9263235294
903.0924660633 0.0) (11 7036.5677941176 903.0924660633 0.0))
((0 . "LINE") (100 . "AcDbEntity") (8 . "MASONRY") (62 . 7) (370 . 13) (100 . "AcDbLine") (10 7043.7408031674
3212.6696832579 0.0) (11 7043.7408031674 3191.930158371 0.0))
((0 . "LINE") (100 . "AcDbEntity") (8 . "MASONRY") (62 . 7) (370 . 13) (100 . "AcDbLine") (10 7077.6774547511
3191.930158371 0.0) (11 7043.7408031674 3191.930158371 0.0))
((0 . "LINE") (100 . "AcDbEntity") (8 . "MASONRY") (62 . 7) (370 . 13) (100 . "AcDbLine") (10 7055.0523303167
1451.7336199095 0.0) (11 7055.0523303167 1417.7969683258 0.0))
((0 . "LINE") (100 . "AcDbEntity") (8 . "MASONRY") (62 . 7) (370 . 13) (100 . "AcDbLine") (10 7051.281821267
3048.6425339367 0.0) (11 7213.424061086 3048.6425339367 0.0))
((0 . "LINE") (100 . "AcDbEntity") (8 . "MASONRY") (62 . 7) (370 . 13) (100 . "AcDbLine") (10 7051.281821267
2748.8687782805 0.0) (11 7051.281821267 2722.4738348416 0.0))
((0 . "LINE") (100 . "AcDbEntity") (8 . "MASONRY") (62 . 7) (370 . 13) (100 . "AcDbLine") (10 7164.4039932127
2748.8687782805 0.0) (11 7051.281821267 2748.8687782805 0.0))
((0 . "LINE") (100 . "AcDbEntity") (8 . "MASONRY") (62 . 7) (370 . 13) (100 . "AcDbLine") (10 7055.053020362
2635.7466063348 0.0) (11 7153.0917760181 2635.7466063348 0.0))
((0 . "LINE") (100 . "AcDbEntity") (8 . "MASONRY") (62 . 7) (370 . 13) (100 . "AcDbLine") (10 7055.053020362
1625.1894570136 0.0) (11 7426.4705882353 1625.1894570136 0.0))
((0 . "LINE") (100 . "AcDbEntity") (8 . "MASONRY") (62 . 7) (370 . 13) (100 . "AcDbLine") (10 7058.8235294118
2111.6141063348 0.0) (11 7633.8616968326 2111.6141063348 0.0))
((0 . "LINE") (100 . "AcDbEntity") (8 . "MASONRY") (62 . 7) (370 . 13) (100 . "AcDbLine") (10 7467.9482579186
1417.7969683258 0.0) (11 7190.7996266968 1417.7969683258 0.0))
((0 . "LINE") (100 . "AcDbEntity") (8 . "MASONRY") (62 . 7) (370 . 13) (100 . "AcDbLine") (10 7190.7996266968
1417.7969683258 0.0) (11 7164.4039932127 1417.7969683258 0.0))
((0 . "LINE") (100 . "AcDbEntity") (8 . "MASONRY") (62 . 7) (370 . 13) (100 . "AcDbLine") (10 7164.4039932127
1417.7969683258 0.0) (11 7055.0523303167 1417.7969683258 0.0))
((0 . "LINE") (100 . "AcDbEntity") (8 . "MASONRY") (62 . 7) (370 . 13) (100 . "AcDbLine") (10 7062.5940384615
1168.9281900452 0.0) (11 7115.3846153846 1168.9281900452 0.0))
((0 . "LINE") (100 . "AcDbEntity") (8 . "MASONRY") (62 . 7) (370 . 13) (100 . "AcDbLine") (10 7073.9062556561
1451.7336199095 0.0) (11 7130.467341629 1451.7336199095 0.0))
((0 . "LINE") (100 . "AcDbEntity") (8 . "MASONRY") (62 . 7) (370 . 13) (100 . "AcDbLine") (10 7277.5261651584
1549.7737556561 0.0) (11 7077.6774547511 1549.7737556561 0.0))
((0 . "LINE") (100 . "AcDbEntity") (8 . "MASONRY") (62 . 7) (370 . 13) (100 . "AcDbLine") (10 7030.8978733032
682.5774208145 0.0) (11 6987.134841629 682.5774208145 0.0))
((0 . "LINE") (100 . "AcDbEntity") (8 . "MASONRY") (62 . 7) (370 . 13) (100 . "AcDbLine") (10 6987.134841629
682.5774208145 0.0) (11 6987.134841629 599.5675339367 0.0))
((0 . "LINE") (100 . "AcDbEntity") (8 . "MASONRY") (62 . 7) (370 . 13) (100 . "AcDbLine") (10 7175.7162104072
3342.7601809955 0.0) (11 7081.4479638009 3342.7601809955 0.0))
((0 . "LINE") (100 . "AcDbEntity") (8 . "MASONRY") (62 . 7) (370 . 13) (100 . "AcDbLine") (10 7209.652861991
3190.0452488688 0.0) (11 7115.3846153846 3190.0452488688 0.0))
((0 . "LINE") (100 . "AcDbEntity") (8 . "MASONRY") (62 . 7) (370 . 13) (100 . "AcDbLine") (10 7126.6968325792
1742.0814479638 0.0) (11 7126.6968325792 1708.1447963801 0.0))
((0 . "LINE") (100 . "AcDbEntity") (8 . "MASONRY") (62 . 7) (370 . 13) (100 . "AcDbLine") (10 7126.6968325792
1742.0814479638 0.0) (11 7334.0872511312 1742.0814479638 0.0))
((0 . "LINE") (100 . "AcDbEntity") (8 . "MASONRY") (62 . 7) (370 . 13) (100 . "AcDbLine") (10 7168.1751923077
1167.043280543 0.0) (11 7126.6968325792 1167.043280543 0.0))
((0 . "LINE") (100 . "AcDbEntity") (8 . "MASONRY") (62 . 7) (370 . 13) (100 . "AcDbLine") (10 7139.893959276
2254.9017307692 0.0) (11 7139.893959276 2271.8707466063 0.0))
((0 . "LINE") (100 . "AcDbEntity") (8 . "MASONRY") (62 . 7) (370 . 13) (100 . "AcDbLine") (10 7139.893959276
2271.8707466063 0.0) (11 7224.7362782805 2271.8707466063 0.0))
((0 . "LINE") (100 . "AcDbEntity") (8 . "MASONRY") (62 . 7) (370 . 13) (100 . "AcDbLine") (10 7205.8823529412
2547.1344683258 0.0) (11 7145.5507579186 2547.1344683258 0.0))
((0 . "LINE") (100 . "AcDbEntity") (8 . "MASONRY") (62 . 7) (370 . 13) (100 . "AcDbLine") (10 7153.0917760181
2635.7466063348 0.0) (11 7153.0917760181 2620.6638800905 0.0))
((0 . "LINE") (100 . "AcDbEntity") (8 . "MASONRY") (62 . 7) (370 . 13) (100 . "AcDbLine") (10 7153.0917760181
2635.7466063348 0.0) (11 7213.424061086 2635.7466063348 0.0))
((0 . "LINE") (100 . "AcDbEntity") (8 . "MASONRY") (62 . 7) (370 . 13) (100 . "AcDbLine") (10 7175.7162104072
1926.8474321267 0.0) (11 7156.8629751131 1926.8474321267 0.0))
((0 . "LINE") (100 . "AcDbEntity") (8 . "MASONRY") (62 . 7) (370 . 13) (100 . "AcDbLine") (10 7164.4039932127
2771.4932126697 0.0) (11 7164.4039932127 2748.8687782805 0.0))
((0 . "LINE") (100 . "AcDbEntity") (8 . "MASONRY") (62 . 7) (370 . 13) (100 . "AcDbLine") (10 7177.6018099548
2748.8687782805 0.0) (11 7164.4039932127 2748.8687782805 0.0))
((0 . "LINE") (100 . "AcDbEntity") (8 . "MASONRY") (62 . 7) (370 . 13) (100 . "AcDbLine") (10 7190.7996266968
1014.4767986425 0.0) (11 7164.4039932127 1014.4767986425 0.0))
((0 . "LINE") (100 . "AcDbEntity") (8 . "MASONRY") (62 . 7) (370 . 13) (100 . "AcDbLine") (10 7179.4874095023
1987.1797171946 0.0) (11 7173.831300905 1987.1797171946 0.0))
((0 . "LINE") (100 . "AcDbEntity") (8 . "MASONRY") (62 . 7) (370 . 13) (100 . "AcDbLine") (10 7173.831300905
1987.1797171946 0.0) (11 7173.831300905 2009.8041515837 0.0))
((0 . "LINE") (100 . "AcDbEntity") (8 . "MASONRY") (62 . 7) (370 . 13) (100 . "AcDbLine") (10 7175.7162104072
1926.8474321267 0.0) (11 7175.7162104072 1864.6309276018 0.0))
((0 . "LINE") (100 . "AcDbEntity") (8 . "MASONRY") (62 . 7) (370 . 13) (100 . "AcDbLine") (10 7175.7162104072
1864.6309276018 0.0) (11 7328.4318325792 1864.6309276018 0.0))
((0 . "LINE") (100 . "AcDbEntity") (8 . "MASONRY") (62 . 7) (370 . 13) (100 . "AcDbLine") (10 7175.7162104072
1934.3891402715 0.0) (11 7175.7162104072 1926.8474321267 0.0))
((0 . "LINE") (100 . "AcDbEntity") (8 . "MASONRY") (62 . 7) (370 . 13) (100 . "AcDbLine") (10 7177.6018099548
3367.2702149321 0.0) (11 7177.6018099548 3404.9773755656 0.0))
((0 . "LINE") (100 . "AcDbEntity") (8 . "MASONRY") (62 . 7) (370 . 13) (100 . "AcDbLine") (10 7175.7162104072
3288.0846945701 0.0) (11 7175.7162104072 3257.9185520362 0.0))
((0 . "LINE") (100 . "AcDbEntity") (8 . "MASONRY") (62 . 7) (370 . 13) (100 . "AcDbLine") (10 7175.7162104072
3257.9185520362 0.0) (11 7213.424061086 3257.9185520362 0.0))
((0 . "LINE") (100 . "AcDbEntity") (8 . "MASONRY") (62 . 7) (370 . 13) (100 . "AcDbLine") (10 7177.6018099548
2748.8687782805 0.0) (11 7213.424061086 2748.8687782805 0.0))
((0 . "LINE") (100 . "AcDbEntity") (8 . "MASONRY") (62 . 7) (370 . 13) (100 . "AcDbLine") (10 7177.6018099548
2748.8687782805 0.0) (11 7177.6018099548 2722.4738348416 0.0))
((0 . "LINE") (100 . "AcDbEntity") (8 . "MASONRY") (62 . 7) (370 . 13) (100 . "AcDbLine") (10 7175.7162104072
1334.8416289593 0.0) (11 7175.7162104072 1376.320678733 0.0))
((0 . "LINE") (100 . "AcDbEntity") (8 . "MASONRY") (62 . 7) (370 . 13) (100 . "AcDbLine") (10 7688.5378733032
1334.8416289593 0.0) (11 7175.7162104072 1334.8416289593 0.0))
((0 . "LINE") (100 . "AcDbEntity") (8 . "MASONRY") (62 . 7) (370 . 13) (100 . "AcDbLine") (10 7179.4874095023
874.8105429864 0.0) (11 7179.4874095023 867.2709049774 0.0))
((0 . "LINE") (100 . "AcDbEntity") (8 . "MASONRY") (62 . 7) (370 . 13) (100 . "AcDbLine") (10 7179.4874095023
867.2709049774 0.0) (11 7179.4874095023 814.479638009 0.0))
((0 . "LINE") (100 . "AcDbEntity") (8 . "MASONRY") (62 . 7) (370 . 13) (100 . "AcDbLine") (10 7179.4874095023
814.479638009 0.0) (11 7179.4874095023 778.1526696833 0.0))
((0 . "LINE") (100 . "AcDbEntity") (8 . "MASONRY") (62 . 7) (370 . 13) (100 . "AcDbLine") (10 7179.4874095023
778.1526696833 0.0) (11 7179.4874095023 727.751719457 0.0))
((0 . "LINE") (100 . "AcDbEntity") (8 . "MASONRY") (62 . 7) (370 . 13) (100 . "AcDbLine") (10 7179.4874095023
727.751719457 0.0) (11 7179.4874095023 665.0374095023 0.0))
((0 . "LINE") (100 . "AcDbEntity") (8 . "MASONRY") (62 . 7) (370 . 13) (100 . "AcDbLine") (10 7190.7996266968
1468.7033257919 0.0) (11 7183.257918552 1468.7033257919 0.0))
((0 . "LINE") (100 . "AcDbEntity") (8 . "MASONRY") (62 . 7) (370 . 13) (100 . "AcDbLine") (10 7183.257918552
1165.1583710407 0.0) (11 7220.9650791855 1165.1583710407 0.0))
((0 . "LINE") (100 . "AcDbEntity") (8 . "MASONRY") (62 . 7) (370 . 13) (100 . "AcDbLine") (10 7194.5701357466
764.1919117647 0.0) (11 7189.4967647059 764.1919117647 0.0))
((0 . "LINE") (100 . "AcDbEntity") (8 . "MASONRY") (62 . 7) (370 . 13) (100 . "AcDbLine") (10 7190.7996266968
1014.4767986425 0.0) (11 7190.7996266968 938.9140271493 0.0))
((0 . "LINE") (100 . "AcDbEntity") (8 . "MASONRY") (62 . 7) (370 . 13) (100 . "AcDbLine") (10 7190.7996266968
1014.4767986425 0.0) (11 7373.6807013575 1014.4767986425 0.0))
((0 . "LINE") (100 . "AcDbEntity") (8 . "MASONRY") (62 . 7) (370 . 13) (100 . "AcDbLine") (10 7228.5067873303
2013.5746606335 0.0) (11 7213.424061086 2013.5746606335 0.0))
((0 . "LINE") (100 . "AcDbEntity") (8 . "MASONRY") (62 . 7) (370 . 13) (100 . "AcDbLine") (10 7492.4582918552
2271.8707466063 0.0) (11 7243.5895135747 2271.8707466063 0.0))
((0 . "LINE") (100 . "AcDbEntity") (8 . "MASONRY") (62 . 7) (370 . 13) (100 . "AcDbLine") (10 7243.5895135747
2271.8707466063 0.0) (11 7224.7362782805 2271.8707466063 0.0))
((0 . "LINE") (100 . "AcDbEntity") (8 . "MASONRY") (62 . 7) (370 . 13) (100 . "AcDbLine") (10 7224.7362782805
2328.4318325792 0.0) (11 7224.7362782805 2271.8707466063 0.0))
((0 . "LINE") (100 . "AcDbEntity") (8 . "MASONRY") (62 . 7) (370 . 13) (100 . "AcDbLine") (10 7224.7362782805
2328.4318325792 0.0) (11 7224.7362782805 2371.7212217195 0.0))
((0 . "LINE") (100 . "AcDbEntity") (8 . "MASONRY") (62 . 7) (370 . 13) (100 . "AcDbLine") (10 7224.7362782805
2371.7212217195 0.0) (11 7288.8383823529 2371.7212217195 0.0))
((0 . "LINE") (100 . "AcDbEntity") (8 . "MASONRY") (62 . 7) (370 . 13) (100 . "AcDbLine") (10 7224.7362782805
2328.4318325792 0.0) (11 7466.0633484163 2328.4318325792 0.0))
((0 . "LINE") (100 . "AcDbEntity") (8 . "MASONRY") (62 . 7) (370 . 13) (100 . "AcDbLine") (10 7262.443438914
1466.8170361991 0.0) (11 7228.5067873303 1466.8170361991 0.0))
((0 . "LINE") (100 . "AcDbEntity") (8 . "MASONRY") (62 . 7) (370 . 13) (100 . "AcDbLine") (10 7273.7556561086
912.5197737557 0.0) (11 7232.2772963801 912.5197737557 0.0))
((0 . "LINE") (100 . "AcDbEntity") (8 . "MASONRY") (62 . 7) (370 . 13) (100 . "AcDbLine") (10 7262.443438914
1165.1583710407 0.0) (11 7251.1312217195 1165.1583710407 0.0))
((0 . "LINE") (100 . "AcDbEntity") (8 . "MASONRY") (62 . 7) (370 . 13) (100 . "AcDbLine") (10 7273.7556561086
886.122760181 0.0) (11 7254.9017307692 886.122760181 0.0))
((0 . "LINE") (100 . "AcDbEntity") (8 . "MASONRY") (62 . 7) (370 . 13) (100 . "AcDbLine") (10 7262.443438914
1187.7828054299 0.0) (11 7262.443438914 1165.1583710407 0.0))
((0 . "LINE") (100 . "AcDbEntity") (8 . "MASONRY") (62 . 7) (370 . 13) (100 . "AcDbLine") (10 7277.5261651584
2011.6897511312 0.0) (11 7269.9851470588 2011.6897511312 0.0))
((0 . "LINE") (100 . "AcDbEntity") (8 . "MASONRY") (62 . 7) (370 . 13) (100 . "AcDbLine") (10 7345.3994683258
912.5197737557 0.0) (11 7273.7556561086 912.5197737557 0.0))
((0 . "LINE") (100 . "AcDbEntity") (8 . "MASONRY") (62 . 7) (370 . 13) (100 . "AcDbLine") (10 7273.7556561086
912.5197737557 0.0) (11 7273.7556561086 886.122760181 0.0))
((0 . "LINE") (100 . "AcDbEntity") (8 . "MASONRY") (62 . 7) (370 . 13) (100 . "AcDbLine") (10 7338.7739819005
886.122760181 0.0) (11 7273.7556561086 886.122760181 0.0))
((0 . "LINE") (100 . "AcDbEntity") (8 . "MASONRY") (62 . 7) (370 . 13) (100 . "AcDbLine") (10 7288.8383823529
824.7161425339 0.0) (11 7324.9561425339 824.7161425339 0.0))
((0 . "LINE") (100 . "AcDbEntity") (8 . "MASONRY") (62 . 7) (370 . 13) (100 . "AcDbLine") (10 7292.609581448
1197.2087330317 0.0) (11 7311.4628167421 1197.2087330317 0.0))
((0 . "LINE") (100 . "AcDbEntity") (8 . "MASONRY") (62 . 7) (370 . 13) (100 . "AcDbLine") (10 7309.5772171946
1546.0025565611 0.0) (11 7296.3800904977 1546.0025565611 0.0))
((0 . "LINE") (100 . "AcDbEntity") (8 . "MASONRY") (62 . 7) (370 . 13) (100 . "AcDbLine") (10 7300.1505995475
1461.1609276018 0.0) (11 7307.6923076923 1461.1609276018 0.0))
((0 . "LINE") (100 . "AcDbEntity") (8 . "MASONRY") (62 . 7) (370 . 13) (100 . "AcDbLine") (10 7307.6923076923
2388.7634276018 0.0) (11 7322.7750339367 2388.7634276018 0.0))
((0 . "LINE") (100 . "AcDbEntity") (8 . "MASONRY") (62 . 7) (370 . 13) (100 . "AcDbLine") (10 7322.7750339367
2388.7634276018 0.0) (11 7322.7750339367 2428.3561877828 0.0))
((0 . "LINE") (100 . "AcDbEntity") (8 . "MASONRY") (62 . 7) (370 . 13) (100 . "AcDbLine") (10 7567.8733031674
1546.0025565611 0.0) (11 7319.0045248869 1546.0025565611 0.0))
((0 . "LINE") (100 . "AcDbEntity") (8 . "MASONRY") (62 . 7) (370 . 13) (100 . "AcDbLine") (10 7319.0045248869
1546.0025565611 0.0) (11 7309.5772171946 1546.0025565611 0.0))
((0 . "LINE") (100 . "AcDbEntity") (8 . "MASONRY") (62 . 7) (370 . 13) (100 . "AcDbLine") (10 7309.5772171946
1583.7104072398 0.0) (11 7309.5772171946 1546.0025565611 0.0))
((0 . "LINE") (100 . "AcDbEntity") (8 . "MASONRY") (62 . 7) (370 . 13) (100 . "AcDbLine") (10 7311.4628167421
1312.2171945701 0.0) (11 7311.4628167421 1297.135158371 0.0))
((0 . "LINE") (100 . "AcDbEntity") (8 . "MASONRY") (62 . 7) (370 . 13) (100 . "AcDbLine") (10 7375.5656108597
1161.3885520362 0.0) (11 7311.4628167421 1161.3885520362 0.0))
((0 . "LINE") (100 . "AcDbEntity") (8 . "MASONRY") (62 . 7) (370 . 13) (100 . "AcDbLine") (10 7315.2340158371
2496.2294909502 0.0) (11 7330.3167420814 2496.2294909502 0.0))
((0 . "LINE") (100 . "AcDbEntity") (8 . "MASONRY") (62 . 7) (370 . 13) (100 . "AcDbLine") (10 7328.4318325792
1809.9547511312 0.0) (11 7315.2340158371 1809.9547511312 0.0))
((0 . "LINE") (100 . "AcDbEntity") (8 . "MASONRY") (62 . 7) (370 . 13) (100 . "AcDbLine") (10 7322.7750339367
3470.9657692308 0.0) (11 7322.7750339367 3514.3290384615 0.0))
((0 . "LINE") (100 . "AcDbEntity") (8 . "MASONRY") (62 . 7) (370 . 13) (100 . "AcDbLine") (10 7322.7750339367
3536.9534728507 0.0) (11 7322.7750339367 3514.3290384615 0.0))
((0 . "LINE") (100 . "AcDbEntity") (8 . "MASONRY") (62 . 7) (370 . 13) (100 . "AcDbLine") (10 7319.0045248869
1973.9819004525 0.0) (11 7368.0239027149 1973.9819004525 0.0))
((0 . "LINE") (100 . "AcDbEntity") (8 . "MASONRY") (62 . 7) (370 . 13) (100 . "AcDbLine") (10 7322.7750339367
2428.3561877828 0.0) (11 7322.7750339367 2458.5216402715 0.0))
((0 . "LINE") (100 . "AcDbEntity") (8 . "MASONRY") (62 . 7) (370 . 13) (100 . "AcDbLine") (10 7322.7750339367
2428.3561877828 0.0) (11 7456.636040724 2428.3561877828 0.0))
((0 . "LINE") (100 . "AcDbEntity") (8 . "MASONRY") (62 . 7) (370 . 13) (100 . "AcDbLine") (10 7322.7750339367
3470.9657692308 0.0) (11 7865.7607692308 3470.9657692308 0.0))
((0 . "LINE") (100 . "AcDbEntity") (8 . "MASONRY") (62 . 7) (370 . 13) (100 . "AcDbLine") (10 7371.79510181
2011.6897511312 0.0) (11 7326.5462330317 2011.6897511312 0.0))
((0 . "LINE") (100 . "AcDbEntity") (8 . "MASONRY") (62 . 7) (370 . 13) (100 . "AcDbLine") (10 7328.4318325792
1864.6309276018 0.0) (11 7328.4318325792 1809.9547511312 0.0))
((0 . "LINE") (100 . "AcDbEntity") (8 . "MASONRY") (62 . 7) (370 . 13) (100 . "AcDbLine") (10 7415.1583710407
1864.6309276018 0.0) (11 7328.4318325792 1864.6309276018 0.0))
((0 . "LINE") (100 . "AcDbEntity") (8 . "MASONRY") (62 . 7) (370 . 13) (100 . "AcDbLine") (10 7492.4582918552
1809.9547511312 0.0) (11 7328.4318325792 1809.9547511312 0.0))
((0 . "LINE") (100 . "AcDbEntity") (8 . "MASONRY") (62 . 7) (370 . 13) (100 . "AcDbLine") (10 7334.0872511312
1768.4757013575 0.0) (11 7334.0872511312 1742.0814479638 0.0))
((0 . "LINE") (100 . "AcDbEntity") (8 . "MASONRY") (62 . 7) (370 . 13) (100 . "AcDbLine") (10 7492.4582918552
1742.0814479638 0.0) (11 7334.0872511312 1742.0814479638 0.0))
((0 . "LINE") (100 . "AcDbEntity") (8 . "MASONRY") (62 . 7) (370 . 13) (100 . "AcDbLine") (10 7345.3994683258
912.5197737557 0.0) (11 7345.3994683258 885.4958371041 0.0))
((0 . "LINE") (100 . "AcDbEntity") (8 . "MASONRY") (62 . 7) (370 . 13) (100 . "AcDbLine") (10 7345.3994683258
912.5197737557 0.0) (11 7364.2533936652 912.5197737557 0.0))
((0 . "LINE") (100 . "AcDbEntity") (8 . "MASONRY") (62 . 7) (370 . 13) (100 . "AcDbLine") (10 7347.1138348416
881.7819457014 0.0) (11 7356.1676131222 881.7819457014 0.0))
((0 . "LINE") (100 . "AcDbEntity") (8 . "MASONRY") (62 . 7) (370 . 13) (100 . "AcDbLine") (10 7374.6224660633
823.9856561086 0.0) (11 7401.9605542986 823.9856561086 0.0))
((0 . "LINE") (100 . "AcDbEntity") (8 . "MASONRY") (62 . 7) (370 . 13) (100 . "AcDbLine") (10 7356.1676131222
863.3450452489 0.0) (11 7356.1676131222 881.7819457014 0.0))
((0 . "LINE") (100 . "AcDbEntity") (8 . "MASONRY") (62 . 7) (370 . 13) (100 . "AcDbLine") (10 7462.2928393665
881.7819457014 0.0) (11 7356.1676131222 881.7819457014 0.0))
((0 . "LINE") (100 . "AcDbEntity") (8 . "MASONRY") (62 . 7) (370 . 13) (100 . "AcDbLine") (10 7594.2675565611
1259.4273076923 0.0) (11 7360.4828846154 1259.4273076923 0.0))
((0 . "LINE") (100 . "AcDbEntity") (8 . "MASONRY") (62 . 7) (370 . 13) (100 . "AcDbLine") (10 7500 1104.8274660633 0.0)
(11 7500 1087.9350904977 0.0))
((0 . "LINE") (100 . "AcDbEntity") (8 . "MASONRY") (62 . 7) (370 . 13) (100 . "AcDbLine") (10 7500 1087.9350904977 0.0)
(11 7371.79510181 1087.9350904977 0.0))
((0 . "LINE") (100 . "AcDbEntity") (8 . "MASONRY") (62 . 7) (370 . 13) (100 . "AcDbLine") (10 7373.6807013575
1055.8060180995 0.0) (11 7373.6807013575 1014.4767986425 0.0))
((0 . "LINE") (100 . "AcDbEntity") (8 . "MASONRY") (62 . 7) (370 . 13) (100 . "AcDbLine") (10 7435.8260859729
747.234638009 0.0) (11 7435.8260859729 812.5167081448 0.0))
((0 . "LINE") (100 . "AcDbEntity") (8 . "MASONRY") (62 . 7) (370 . 13) (100 . "AcDbLine") (10 7435.8260859729
812.5167081448 0.0) (11 7490.0451923077 812.5167081448 0.0))
((0 . "LINE") (100 . "AcDbEntity") (8 . "MASONRY") (62 . 7) (370 . 13) (100 . "AcDbLine") (10 7375.5656108597
1127.4519004525 0.0) (11 7375.5656108597 1161.3885520362 0.0))
((0 . "LINE") (100 . "AcDbEntity") (8 . "MASONRY") (62 . 7) (370 . 13) (100 . "AcDbLine") (10 7462.2928393665
1161.3885520362 0.0) (11 7375.5656108597 1161.3885520362 0.0))
((0 . "LINE") (100 . "AcDbEntity") (8 . "MASONRY") (62 . 7) (370 . 13) (100 . "AcDbLine") (10 7481.1460746606
1014.4767986425 0.0) (11 7409.5022624434 1014.4767986425 0.0))
((0 . "LINE") (100 . "AcDbEntity") (8 . "MASONRY") (62 . 7) (370 . 13) (100 . "AcDbLine") (10 7409.5022624434
1014.4767986425 0.0) (11 7373.6807013575 1014.4767986425 0.0))
((0 . "LINE") (100 . "AcDbEntity") (8 . "MASONRY") (62 . 7) (370 . 13) (100 . "AcDbLine") (10 7490.0451923077
664.2496153846 0.0) (11 7490.0451923077 791.8552036199 0.0))
((0 . "LINE") (100 . "AcDbEntity") (8 . "MASONRY") (62 . 7) (370 . 13) (100 . "AcDbLine") (10 7490.0451923077
791.8552036199 0.0) (11 7490.0451923077 812.5167081448 0.0))
((0 . "LINE") (100 . "AcDbEntity") (8 . "MASONRY") (62 . 7) (370 . 13) (100 . "AcDbLine") (10 7417.043280543
1896.681979638 0.0) (11 7417.043280543 1915.5352149321 0.0))
((0 . "LINE") (100 . "AcDbEntity") (8 . "MASONRY") (62 . 7) (370 . 13) (100 . "AcDbLine") (10 7415.1583710407
1864.6309276018 0.0) (11 7415.1583710407 1877.8280542986 0.0))
((0 . "LINE") (100 . "AcDbEntity") (8 . "MASONRY") (62 . 7) (370 . 13) (100 . "AcDbLine") (10 7415.1583710407
1864.6309276018 0.0) (11 7435.8972058824 1864.6309276018 0.0))
((0 . "LINE") (100 . "AcDbEntity") (8 . "MASONRY") (62 . 7) (370 . 13) (100 . "AcDbLine") (10 7419.0062104072
2013.5746606335 0.0) (11 7419.0062104072 1953.3908257919 0.0))
((0 . "LINE") (100 . "AcDbEntity") (8 . "MASONRY") (62 . 7) (370 . 13) (100 . "AcDbLine") (10 7419.0062104072
1953.3908257919 0.0) (11 7439.6684049774 1953.3908257919 0.0))
((0 . "LINE") (100 . "AcDbEntity") (8 . "MASONRY") (62 . 7) (370 . 13) (100 . "AcDbLine") (10 7439.6684049774
1953.3908257919 0.0) (11 7726.2443438914 1953.3908257919 0.0))
((0 . "LINE") (100 . "AcDbEntity") (8 . "MASONRY") (62 . 7) (370 . 13) (100 . "AcDbLine") (10 7435.8972058824
1625.1894570136 0.0) (11 7426.4705882353 1625.1894570136 0.0))
((0 . "LINE") (100 . "AcDbEntity") (8 . "MASONRY") (62 . 7) (370 . 13) (100 . "AcDbLine") (10 7426.4705882353
1644.0413122172 0.0) (11 7426.4705882353 1625.1894570136 0.0))
((0 . "LINE") (100 . "AcDbEntity") (8 . "MASONRY") (62 . 7) (370 . 13) (100 . "AcDbLine") (10 7437.7828054299
1372.5480995475 0.0) (11 7437.7828054299 1365.0084615385 0.0))
((0 . "LINE") (100 . "AcDbEntity") (8 . "MASONRY") (62 . 7) (370 . 13) (100 . "AcDbLine") (10 7492.4582918552
2775.2637217195 0.0) (11 7454.7511312217 2775.2637217195 0.0))
((0 . "LINE") (100 . "AcDbEntity") (8 . "MASONRY") (62 . 7) (370 . 13) (100 . "AcDbLine") (10 7696.0775113122
2503.7705090498 0.0) (11 7454.7511312217 2503.7705090498 0.0))
((0 . "LINE") (100 . "AcDbEntity") (8 . "MASONRY") (62 . 7) (370 . 13) (100 . "AcDbLine") (10 7456.636040724
2375.5656108597 0.0) (11 7456.636040724 2428.3561877828 0.0))
((0 . "LINE") (100 . "AcDbEntity") (8 . "MASONRY") (62 . 7) (370 . 13) (100 . "AcDbLine") (10 7456.636040724
2428.3561877828 0.0) (11 7599.9236651584 2428.3561877828 0.0))
((0 . "LINE") (100 . "AcDbEntity") (8 . "MASONRY") (62 . 7) (370 . 13) (100 . "AcDbLine") (10 7458.5216402715
3412.5190837104 0.0) (11 7458.5216402715 3404.9773755656 0.0))
((0 . "LINE") (100 . "AcDbEntity") (8 . "MASONRY") (62 . 7) (370 . 13) (100 . "AcDbLine") (10 7865.7607692308
3340.874581448 0.0) (11 7458.5216402715 3340.874581448 0.0))
((0 . "LINE") (100 . "AcDbEntity") (8 . "MASONRY") (62 . 7) (370 . 13) (100 . "AcDbLine") (10 7869.5333484163
3267.3451696833 0.0) (11 7458.5216402715 3267.3451696833 0.0))
((0 . "LINE") (100 . "AcDbEntity") (8 . "MASONRY") (62 . 7) (370 . 13) (100 . "AcDbLine") (10 7458.5216402715
3191.930158371 0.0) (11 7869.5333484163 3191.930158371 0.0))
((0 . "LINE") (100 . "AcDbEntity") (8 . "MASONRY") (62 . 7) (370 . 13) (100 . "AcDbLine") (10 7500 2818.6269909502 0.0)
(11 7458.5216402715 2818.6269909502 0.0))
((0 . "LINE") (100 . "AcDbEntity") (8 . "MASONRY") (62 . 7) (370 . 13) (100 . "AcDbLine") (10 7458.5216402715
2633.8616968326 0.0) (11 7618.778280543 2633.8616968326 0.0))
((0 . "LINE") (100 . "AcDbEntity") (8 . "MASONRY") (62 . 7) (370 . 13) (100 . "AcDbLine") (10 7460.407239819
2564.1027941176 0.0) (11 7460.407239819 2575.4150113122 0.0))
((0 . "LINE") (100 . "AcDbEntity") (8 . "MASONRY") (62 . 7) (370 . 13) (100 . "AcDbLine") (10 7458.5216402715
1860.78239819 0.0) (11 7492.4582918552 1860.78239819 0.0))
((0 . "LINE") (100 . "AcDbEntity") (8 . "MASONRY") (62 . 7) (370 . 13) (100 . "AcDbLine") (10 7492.4582918552
1860.78239819 0.0) (11 7492.4582918552 1809.9547511312 0.0))
((0 . "LINE") (100 . "AcDbEntity") (8 . "MASONRY") (62 . 7) (370 . 13) (100 . "AcDbLine") (10 7869.5333484163
2894.0426923077 0.0) (11 7462.2928393665 2894.0426923077 0.0))
((0 . "LINE") (100 . "AcDbEntity") (8 . "MASONRY") (62 . 7) (370 . 13) (100 . "AcDbLine") (10 7466.0633484163
3120.2870361991 0.0) (11 7533.9366515837 3120.2870361991 0.0))
((0 . "LINE") (100 . "AcDbEntity") (8 . "MASONRY") (62 . 7) (370 . 13) (100 . "AcDbLine") (10 7466.0633484163
3046.7569343891 0.0) (11 7650.8286425339 3046.7569343891 0.0))
((0 . "LINE") (100 . "AcDbEntity") (8 . "MASONRY") (62 . 7) (370 . 13) (100 . "AcDbLine") (10 7466.0633484163
2969.4570135747 0.0) (11 7598.0401357466 2969.4570135747 0.0))
((0 . "LINE") (100 . "AcDbEntity") (8 . "MASONRY") (62 . 7) (370 . 13) (100 . "AcDbLine") (10 7467.9482579186
1417.7969683258 0.0) (11 7467.9482579186 1402.7149321267 0.0))
((0 . "LINE") (100 . "AcDbEntity") (8 . "MASONRY") (62 . 7) (370 . 13) (100 . "AcDbLine") (10 7861.9909502262
1417.7969683258 0.0) (11 7726.2443438914 1417.7969683258 0.0))
((0 . "LINE") (100 . "AcDbEntity") (8 . "MASONRY") (62 . 7) (370 . 13) (100 . "AcDbLine") (10 7726.2443438914
1417.7969683258 0.0) (11 7613.1221719457 1417.7969683258 0.0))
((0 . "LINE") (100 . "AcDbEntity") (8 . "MASONRY") (62 . 7) (370 . 13) (100 . "AcDbLine") (10 7613.1221719457
1417.7969683258 0.0) (11 7467.9482579186 1417.7969683258 0.0))
((0 . "LINE") (100 . "AcDbEntity") (8 . "MASONRY") (62 . 7) (370 . 13) (100 . "AcDbLine") (10 7473.6050565611
2188.9140271493 0.0) (11 7473.6050565611 2217.1945701357 0.0))
((0 . "LINE") (100 . "AcDbEntity") (8 . "MASONRY") (62 . 7) (370 . 13) (100 . "AcDbLine") (10 7473.6050565611
2188.9140271493 0.0) (11 7479.2604751131 2188.9140271493 0.0))
((0 . "LINE") (100 . "AcDbEntity") (8 . "MASONRY") (62 . 7) (370 . 13) (100 . "AcDbLine") (10 7479.2604751131
2153.0917760181 0.0) (11 7479.2604751131 2188.9140271493 0.0))
((0 . "LINE") (100 . "AcDbEntity") (8 . "MASONRY") (62 . 7) (370 . 13) (100 . "AcDbLine") (10 7477.3755656109
1617.6470588235 0.0) (11 7522.6244343891 1617.6470588235 0.0))
((0 . "LINE") (100 . "AcDbEntity") (8 . "MASONRY") (62 . 7) (370 . 13) (100 . "AcDbLine") (10 7477.3755656109
1161.3885520362 0.0) (11 7492.4582918552 1161.3885520362 0.0))
((0 . "LINE") (100 . "AcDbEntity") (8 . "MASONRY") (62 . 7) (370 . 13) (100 . "AcDbLine") (10 7709.2760180995
2188.9140271493 0.0) (11 7479.2604751131 2188.9140271493 0.0))
((0 . "LINE") (100 . "AcDbEntity") (8 . "MASONRY") (62 . 7) (370 . 13) (100 . "AcDbLine") (10 7601.8099547511
2320.8127941176 0.0) (11 7485.5193438914 2320.8127941176 0.0))
((0 . "LINE") (100 . "AcDbEntity") (8 . "MASONRY") (62 . 7) (370 . 13) (100 . "AcDbLine") (10 7485.5193438914
2320.8127941176 0.0) (11 7485.5193438914 2296.3800904977 0.0))
((0 . "LINE") (100 . "AcDbEntity") (8 . "MASONRY") (62 . 7) (370 . 13) (100 . "AcDbLine") (10 7490.0451923077
812.5167081448 0.0) (11 7490.0451923077 825.7918552036 0.0))
((0 . "LINE") (100 . "AcDbEntity") (8 . "MASONRY") (62 . 7) (370 . 13) (100 . "AcDbLine") (10 7492.4582918552
2775.2637217195 0.0) (11 7492.4582918552 2786.575938914 0.0))
((0 . "LINE") (100 . "AcDbEntity") (8 . "MASONRY") (62 . 7) (370 . 13) (100 . "AcDbLine") (10 7492.4582918552
2775.2637217195 0.0) (11 7511.3122171946 2775.2637217195 0.0))
((0 . "LINE") (100 . "AcDbEntity") (8 . "MASONRY") (62 . 7) (370 . 13) (100 . "AcDbLine") (10 7492.4582918552
1742.0814479638 0.0) (11 7492.4582918552 1809.9547511312 0.0))
((0 . "LINE") (100 . "AcDbEntity") (8 . "MASONRY") (62 . 7) (370 . 13) (100 . "AcDbLine") (10 7492.4582918552
1161.3885520362 0.0) (11 7526.3949434389 1161.3885520362 0.0))
((0 . "LINE") (100 . "AcDbEntity") (8 . "MASONRY") (62 . 7) (370 . 13) (100 . "AcDbLine") (10 7492.4582918552
1161.3885520362 0.0) (11 7492.4582918552 1153.8461538462 0.0))
((0 . "LINE") (100 . "AcDbEntity") (8 . "MASONRY") (62 . 7) (370 . 13) (100 . "AcDbLine") (10 7498.1150904977
3152.3380882353 0.0) (11 7498.1150904977 3159.8791063348 0.0))
((0 . "LINE") (100 . "AcDbEntity") (8 . "MASONRY") (62 . 7) (370 . 13) (100 . "AcDbLine") (10 7492.4582918552
1742.0814479638 0.0) (11 7567.8698529412 1742.0814479638 0.0))
((0 . "LINE") (100 . "AcDbEntity") (8 . "MASONRY") (62 . 7) (370 . 13) (100 . "AcDbLine") (10 7567.8698529412
1742.0814479638 0.0) (11 7567.8698529412 1723.2268325792 0.0))
((0 . "LINE") (100 . "AcDbEntity") (8 . "MASONRY") (62 . 7) (370 . 13) (100 . "AcDbLine") (10 7500 1104.8274660633 0.0)
(11 7500 1119.9095022624 0.0))
((0 . "LINE") (100 . "AcDbEntity") (8 . "MASONRY") (62 . 7) (370 . 13) (100 . "AcDbLine") (10 7500 1104.8274660633 0.0)
(11 7628.2042081448 1104.8274660633 0.0))
((0 . "LINE") (100 . "AcDbEntity") (8 . "MASONRY") (62 . 7) (370 . 13) (100 . "AcDbLine") (10 7530.1661425339
903.0924660633 0.0) (11 7507.5417081448 903.0924660633 0.0))
((0 . "LINE") (100 . "AcDbEntity") (8 . "MASONRY") (62 . 7) (370 . 13) (100 . "AcDbLine") (10 7511.3122171946
1035.0678733032 0.0) (11 7571.6438122172 1035.0678733032 0.0))
((0 . "LINE") (100 . "AcDbEntity") (8 . "MASONRY") (62 . 7) (370 . 13) (100 . "AcDbLine") (10 7633.7802262443
595.8888574661 0.0) (11 7633.7802262443 640.8422171946 0.0))
((0 . "LINE") (100 . "AcDbEntity") (8 . "MASONRY") (62 . 7) (370 . 13) (100 . "AcDbLine") (10 7633.7802262443
640.8422171946 0.0) (11 7624.4343891403 640.8422171946 0.0))
((0 . "LINE") (100 . "AcDbEntity") (8 . "MASONRY") (62 . 7) (370 . 13) (100 . "AcDbLine") (10 7526.3949434389
2775.2637217195 0.0) (11 7652.3738574661 2775.2637217195 0.0))
((0 . "LINE") (100 . "AcDbEntity") (8 . "MASONRY") (62 . 7) (370 . 13) (100 . "AcDbLine") (10 7645.1739140272
727.751719457 0.0) (11 7624.4343891403 727.751719457 0.0))
((0 . "LINE") (100 . "AcDbEntity") (8 . "MASONRY") (62 . 7) (370 . 13) (100 . "AcDbLine") (10 7559.0038687783
729.5800113122 0.0) (11 7526.3949434389 729.5800113122 0.0))
((0 . "LINE") (100 . "AcDbEntity") (8 . "MASONRY") (62 . 7) (370 . 13) (100 . "AcDbLine") (10 7533.9366515837
1862.7453280543 0.0) (11 7601.8099547511 1862.7453280543 0.0))
((0 . "LINE") (100 . "AcDbEntity") (8 . "MASONRY") (62 . 7) (370 . 13) (100 . "AcDbLine") (10 7537.7071606335
2268.0995475113 0.0) (11 7688.5378733032 2268.0995475113 0.0))
((0 . "LINE") (100 . "AcDbEntity") (8 . "MASONRY") (62 . 7) (370 . 13) (100 . "AcDbLine") (10 7537.7071606335
1163.2734615385 0.0) (11 7586.727918552 1163.2734615385 0.0))
((0 . "LINE") (100 . "AcDbEntity") (8 . "MASONRY") (62 . 7) (370 . 13) (100 . "AcDbLine") (10 7703.6199095023
1813.7245701357 0.0) (11 7541.4783597285 1813.7245701357 0.0))
((0 . "LINE") (100 . "AcDbEntity") (8 . "MASONRY") (62 . 7) (370 . 13) (100 . "AcDbLine") (10 7550.9049773756
901.2075565611 0.0) (11 7550.9049773756 893.665158371 0.0))
((0 . "LINE") (100 . "AcDbEntity") (8 . "MASONRY") (62 . 7) (370 . 13) (100 . "AcDbLine") (10 7549.0193778281
822.0220361991 0.0) (11 7615.0989140272 822.0220361991 0.0))
((0 . "LINE") (100 . "AcDbEntity") (8 . "MASONRY") (62 . 7) (370 . 13) (100 . "AcDbLine") (10 7624.4343891403
822.0220361991 0.0) (11 7673.4530769231 822.0220361991 0.0))
((0 . "LINE") (100 . "AcDbEntity") (8 . "MASONRY") (62 . 7) (370 . 13) (100 . "AcDbLine") (10 7560.3315950226
2846.9082239819 0.0) (11 7560.3315950226 2854.4492420814 0.0))
((0 . "LINE") (100 . "AcDbEntity") (8 . "MASONRY") (62 . 7) (370 . 13) (100 . "AcDbLine") (10 7562.2171945701
2824.2837895928 0.0) (11 7562.2171945701 2816.742081448 0.0))
((0 . "LINE") (100 . "AcDbEntity") (8 . "MASONRY") (62 . 7) (370 . 13) (100 . "AcDbLine") (10 7565.9877036199
1617.6470588235 0.0) (11 7565.9877036199 1644.0413122172 0.0))
((0 . "LINE") (100 . "AcDbEntity") (8 . "MASONRY") (62 . 7) (370 . 13) (100 . "AcDbLine") (10 7865.7607692308
3105.2036199095 0.0) (11 7564.1027941176 3105.2036199095 0.0))
((0 . "LINE") (100 . "AcDbEntity") (8 . "MASONRY") (62 . 7) (370 . 13) (100 . "AcDbLine") (10 7861.9909502262
1674.2854751131 0.0) (11 7577.2992307692 1674.2854751131 0.0))
((0 . "LINE") (100 . "AcDbEntity") (8 . "MASONRY") (62 . 7) (370 . 13) (100 . "AcDbLine") (10 7577.2992307692
1674.2854751131 0.0) (11 7577.2992307692 1708.1447963801 0.0))
((0 . "LINE") (100 . "AcDbEntity") (8 . "MASONRY") (62 . 7) (370 . 13) (100 . "AcDbLine") (10 7571.6438122172
1006.7873303167 0.0) (11 7571.6438122172 1035.0678733032 0.0))
((0 . "LINE") (100 . "AcDbEntity") (8 . "MASONRY") (62 . 7) (370 . 13) (100 . "AcDbLine") (10 7571.6438122172
1035.0678733032 0.0) (11 7635.7466063348 1035.0678733032 0.0))
((0 . "LINE") (100 . "AcDbEntity") (8 . "MASONRY") (62 . 7) (370 . 13) (100 . "AcDbLine") (10 7635.7466063348
1035.0678733032 0.0) (11 7861.9909502262 1035.0678733032 0.0))
((0 . "LINE") (100 . "AcDbEntity") (8 . "MASONRY") (62 . 7) (370 . 13) (100 . "AcDbLine") (10 7577.3006108597
867.2709049774 0.0) (11 7577.3006108597 920.0594117647 0.0))
((0 . "LINE") (100 . "AcDbEntity") (8 . "MASONRY") (62 . 7) (370 . 13) (100 . "AcDbLine") (10 7579.185520362
959.6535520362 0.0) (11 7835.5966968326 959.6535520362 0.0))
((0 . "LINE") (100 . "AcDbEntity") (8 . "MASONRY") (62 . 7) (370 . 13) (100 . "AcDbLine") (10 7599.9236651584
2450.9806221719 0.0) (11 7599.9236651584 2428.3561877828 0.0))
((0 . "LINE") (100 . "AcDbEntity") (8 . "MASONRY") (62 . 7) (370 . 13) (100 . "AcDbLine") (10 7639.5164253394
2428.3561877828 0.0) (11 7599.9236651584 2428.3561877828 0.0))
((0 . "LINE") (100 . "AcDbEntity") (8 . "MASONRY") (62 . 7) (370 . 13) (100 . "AcDbLine") (10 7861.9909502262
2971.3426131222 0.0) (11 7609.3523529412 2971.3426131222 0.0))
((0 . "LINE") (100 . "AcDbEntity") (8 . "MASONRY") (62 . 7) (370 . 13) (100 . "AcDbLine") (10 7620.6645701357
2552.7905769231 0.0) (11 7613.1221719457 2552.7905769231 0.0))
((0 . "LINE") (100 . "AcDbEntity") (8 . "MASONRY") (62 . 7) (370 . 13) (100 . "AcDbLine") (10 7618.778280543
2605.5804638009 0.0) (11 7618.778280543 2633.8616968326 0.0))
((0 . "LINE") (100 . "AcDbEntity") (8 . "MASONRY") (62 . 7) (370 . 13) (100 . "AcDbLine") (10 7648.9437330317
2633.8616968326 0.0) (11 7618.778280543 2633.8616968326 0.0))
((0 . "LINE") (100 . "AcDbEntity") (8 . "MASONRY") (62 . 7) (370 . 13) (100 . "AcDbLine") (10 7865.7607692308
1591.2514253394 0.0) (11 7616.8919909502 1591.2514253394 0.0))
((0 . "LINE") (100 . "AcDbEntity") (8 . "MASONRY") (62 . 7) (370 . 13) (100 . "AcDbLine") (10 7616.8919909502
1263.1985067873 0.0) (11 7641.4027149321 1263.1985067873 0.0))
((0 . "LINE") (100 . "AcDbEntity") (8 . "MASONRY") (62 . 7) (370 . 13) (100 . "AcDbLine") (10 7620.6645701357
1540.3464479638 0.0) (11 7631.9767873303 1540.3464479638 0.0))
((0 . "LINE") (100 . "AcDbEntity") (8 . "MASONRY") (62 . 7) (370 . 13) (100 . "AcDbLine") (10 7620.6645701357
1474.3580542986 0.0) (11 7699.8500904977 1474.3580542986 0.0))
((0 . "LINE") (100 . "AcDbEntity") (8 . "MASONRY") (62 . 7) (370 . 13) (100 . "AcDbLine") (10 7624.4343891403
1742.0814479638 0.0) (11 7688.5378733032 1742.0814479638 0.0))
((0 . "LINE") (100 . "AcDbEntity") (8 . "MASONRY") (62 . 7) (370 . 13) (100 . "AcDbLine") (10 7628.2042081448
1244.3438914027 0.0) (11 7641.4027149321 1244.3438914027 0.0))
((0 . "LINE") (100 . "AcDbEntity") (8 . "MASONRY") (62 . 7) (370 . 13) (100 . "AcDbLine") (10 7628.2042081448
1134.9915384615 0.0) (11 7628.2042081448 1104.8274660633 0.0))
((0 . "LINE") (100 . "AcDbEntity") (8 . "MASONRY") (62 . 7) (370 . 13) (100 . "AcDbLine") (10 7628.2042081448
1070.8908144796 0.0) (11 7628.2042081448 1104.8274660633 0.0))
((0 . "LINE") (100 . "AcDbEntity") (8 . "MASONRY") (62 . 7) (370 . 13) (100 . "AcDbLine") (10 7631.9767873303
2586.7272285068 0.0) (11 7822.3981900452 2586.7272285068 0.0))
((0 . "LINE") (100 . "AcDbEntity") (8 . "MASONRY") (62 . 7) (370 . 13) (100 . "AcDbLine") (10 7633.8616968326
2077.6774547511 0.0) (11 7633.8616968326 2111.6141063348 0.0))
((0 . "LINE") (100 . "AcDbEntity") (8 . "MASONRY") (62 . 7) (370 . 13) (100 . "AcDbLine") (10 7633.8616968326
2111.6141063348 0.0) (11 7861.9909502262 2111.6141063348 0.0))
((0 . "LINE") (100 . "AcDbEntity") (8 . "MASONRY") (62 . 7) (370 . 13) (100 . "AcDbLine") (10 7639.5164253394
2009.8041515837 0.0) (11 7639.5164253394 2032.4285859729 0.0))
((0 . "LINE") (100 . "AcDbEntity") (8 . "MASONRY") (62 . 7) (370 . 13) (100 . "AcDbLine") (10 7865.7607692308
1163.2734615385 0.0) (11 7631.9767873303 1163.2734615385 0.0))
((0 . "LINE") (100 . "AcDbEntity") (8 . "MASONRY") (62 . 7) (370 . 13) (100 . "AcDbLine") (10 7805.4298642534
3529.4117647059 0.0) (11 7635.7466063348 3529.4117647059 0.0))
((0 . "LINE") (100 . "AcDbEntity") (8 . "MASONRY") (62 . 7) (370 . 13) (100 . "AcDbLine") (10 7639.5164253394
2371.79510181 0.0) (11 7639.5164253394 2401.9605542986 0.0))
((0 . "LINE") (100 . "AcDbEntity") (8 . "MASONRY") (62 . 7) (370 . 13) (100 . "AcDbLine") (10 7641.4027149321
1263.1985067873 0.0) (11 7641.4027149321 1244.3438914027 0.0))
((0 . "LINE") (100 . "AcDbEntity") (8 . "MASONRY") (62 . 7) (370 . 13) (100 . "AcDbLine") (10 7641.4027149321
1263.1985067873 0.0) (11 7641.4027149321 1297.135158371 0.0))
((0 . "LINE") (100 . "AcDbEntity") (8 . "MASONRY") (62 . 7) (370 . 13) (100 . "AcDbLine") (10 7639.5164253394
2428.3561877828 0.0) (11 7639.5164253394 2401.9605542986 0.0))
((0 . "LINE") (100 . "AcDbEntity") (8 . "MASONRY") (62 . 7) (370 . 13) (100 . "AcDbLine") (10 7639.5164253394
2428.3561877828 0.0) (11 7692.3035520362 2428.3561877828 0.0))
((0 . "LINE") (100 . "AcDbEntity") (8 . "MASONRY") (62 . 7) (370 . 13) (100 . "AcDbLine") (10 7692.3035520362
2428.3561877828 0.0) (11 7692.3035520362 2401.9605542986 0.0))
((0 . "LINE") (100 . "AcDbEntity") (8 . "MASONRY") (62 . 7) (370 . 13) (100 . "AcDbLine") (10 7861.9909502262
2322.8530542986 0.0) (11 7645.1725339367 2322.8530542986 0.0))
((0 . "LINE") (100 . "AcDbEntity") (8 . "MASONRY") (62 . 7) (370 . 13) (100 . "AcDbLine") (10 7645.1725339367
2322.8530542986 0.0) (11 7645.1725339367 2352.9411764706 0.0))
((0 . "LINE") (100 . "AcDbEntity") (8 . "MASONRY") (62 . 7) (370 . 13) (100 . "AcDbLine") (10 7639.5164253394
2009.8041515837 0.0) (11 7639.5164253394 1990.9502262443 0.0))
((0 . "LINE") (100 . "AcDbEntity") (8 . "MASONRY") (62 . 7) (370 . 13) (100 . "AcDbLine") (10 7639.5164253394
1864.6302375566 0.0) (11 7707.3897285068 1864.6302375566 0.0))
((0 . "LINE") (100 . "AcDbEntity") (8 . "MASONRY") (62 . 7) (370 . 13) (100 . "AcDbLine") (10 7641.4027149321
1297.135158371 0.0) (11 7641.4027149321 1308.4473755656 0.0))
((0 . "LINE") (100 . "AcDbEntity") (8 . "MASONRY") (62 . 7) (370 . 13) (100 . "AcDbLine") (10 7641.4027149321
1229.2618552036 0.0) (11 7641.4027149321 1244.3438914027 0.0))
((0 . "LINE") (100 . "AcDbEntity") (8 . "MASONRY") (62 . 7) (370 . 13) (100 . "AcDbLine") (10 7639.5164253394
2401.9605542986 0.0) (11 7692.3035520362 2401.9605542986 0.0))
((0 . "LINE") (100 . "AcDbEntity") (8 . "MASONRY") (62 . 7) (370 . 13) (100 . "AcDbLine") (10 7639.5164253394
2009.8041515837 0.0) (11 7865.7607692308 2009.8041515837 0.0))
((0 . "LINE") (100 . "AcDbEntity") (8 . "MASONRY") (62 . 7) (370 . 13) (100 . "AcDbLine") (10 7641.4027149321
1297.135158371 0.0) (11 7688.5378733032 1297.135158371 0.0))
((0 . "LINE") (100 . "AcDbEntity") (8 . "MASONRY") (62 . 7) (370 . 13) (100 . "AcDbLine") (10 7641.4027149321
1199.0950226244 0.0) (11 7641.4027149321 1229.2618552036 0.0))
((0 . "LINE") (100 . "AcDbEntity") (8 . "MASONRY") (62 . 7) (370 . 13) (100 . "AcDbLine") (10 7645.1739140272
727.751719457 0.0) (11 7645.1739140272 701.3574660633 0.0))
((0 . "LINE") (100 . "AcDbEntity") (8 . "MASONRY") (62 . 7) (370 . 13) (100 . "AcDbLine") (10 7645.1739140272
727.751719457 0.0) (11 7861.9909502262 727.751719457 0.0))
((0 . "LINE") (100 . "AcDbEntity") (8 . "MASONRY") (62 . 7) (370 . 13) (100 . "AcDbLine") (10 7647.0588235294
3416.2895927602 0.0) (11 7647.0588235294 3423.831300905 0.0))
((0 . "LINE") (100 . "AcDbEntity") (8 . "MASONRY") (62 . 7) (370 . 13) (100 . "AcDbLine") (10 7647.0588235294
3391.7795588235 0.0) (11 7699.8500904977 3391.7795588235 0.0))
((0 . "LINE") (100 . "AcDbEntity") (8 . "MASONRY") (62 . 7) (370 . 13) (100 . "AcDbLine") (10 7648.9437330317
2633.8616968326 0.0) (11 7869.5333484163 2633.8616968326 0.0))
((0 . "LINE") (100 . "AcDbEntity") (8 . "MASONRY") (62 . 7) (370 . 13) (100 . "AcDbLine") (10 7648.9437330317
2633.8616968326 0.0) (11 7648.9437330317 2688.5371832579 0.0))
((0 . "LINE") (100 . "AcDbEntity") (8 . "MASONRY") (62 . 7) (370 . 13) (100 . "AcDbLine") (10 7641.4027149321
1229.2618552036 0.0) (11 7665.913438914 1229.2618552036 0.0))
((0 . "LINE") (100 . "AcDbEntity") (8 . "MASONRY") (62 . 7) (370 . 13) (100 . "AcDbLine") (10 7714.9321266968
2722.658178733 0.0) (11 7652.3738574661 2722.658178733 0.0))
((0 . "LINE") (100 . "AcDbEntity") (8 . "MASONRY") (62 . 7) (370 . 13) (100 . "AcDbLine") (10 7652.3738574661
2722.658178733 0.0) (11 7652.3738574661 2775.2637217195 0.0))
((0 . "LINE") (100 . "AcDbEntity") (8 . "MASONRY") (62 . 7) (370 . 13) (100 . "AcDbLine") (10 7865.7607692308
2775.2637217195 0.0) (11 7652.3738574661 2775.2637217195 0.0))
((0 . "LINE") (100 . "AcDbEntity") (8 . "MASONRY") (62 . 7) (370 . 13) (100 . "AcDbLine") (10 7669.6832579186
3046.7569343891 0.0) (11 7692.3076923077 3046.7569343891 0.0))
((0 . "LINE") (100 . "AcDbEntity") (8 . "MASONRY") (62 . 7) (370 . 13) (100 . "AcDbLine") (10 7711.1623076923
563.7259502262 0.0) (11 7677.2256561086 563.7259502262 0.0))
((0 . "LINE") (100 . "AcDbEntity") (8 . "MASONRY") (62 . 7) (370 . 13) (100 . "AcDbLine") (10 7865.7607692308
1231.1467647059 0.0) (11 7680.9954751131 1231.1467647059 0.0))
((0 . "LINE") (100 . "AcDbEntity") (8 . "MASONRY") (62 . 7) (370 . 13) (100 . "AcDbLine") (10 7692.3076923077
1547.8888461538 0.0) (11 7865.7607692308 1547.8888461538 0.0))
((0 . "LINE") (100 . "AcDbEntity") (8 . "MASONRY") (62 . 7) (370 . 13) (100 . "AcDbLine") (10 7696.0775113122
2458.5216402715 0.0) (11 7696.0775113122 2503.7705090498 0.0))
((0 . "LINE") (100 . "AcDbEntity") (8 . "MASONRY") (62 . 7) (370 . 13) (100 . "AcDbLine") (10 7696.0775113122
2503.7705090498 0.0) (11 7869.5333484163 2503.7705090498 0.0))
((0 . "LINE") (100 . "AcDbEntity") (8 . "MASONRY") (62 . 7) (370 . 13) (100 . "AcDbLine") (10 7730.0141628959
2401.9605542986 0.0) (11 7692.3035520362 2401.9605542986 0.0))
((0 . "LINE") (100 . "AcDbEntity") (8 . "MASONRY") (62 . 7) (370 . 13) (100 . "AcDbLine") (10 7709.2760180995
2188.9140271493 0.0) (11 7709.2760180995 2149.3212669683 0.0))
((0 . "LINE") (100 . "AcDbEntity") (8 . "MASONRY") (62 . 7) (370 . 13) (100 . "AcDbLine") (10 7709.2760180995
2188.9140271493 0.0) (11 7779.0356108597 2188.9140271493 0.0))
((0 . "LINE") (100 . "AcDbEntity") (8 . "MASONRY") (62 . 7) (370 . 13) (100 . "AcDbLine") (10 7869.5333484163
818.2494570136 0.0) (11 7854.4485520362 818.2494570136 0.0))
((0 . "LINE") (100 . "AcDbEntity") (8 . "MASONRY") (62 . 7) (370 . 13) (100 . "AcDbLine") (10 7854.4485520362
818.2494570136 0.0) (11 7707.3897285068 818.2494570136 0.0))
((0 . "LINE") (100 . "AcDbEntity") (8 . "MASONRY") (62 . 7) (370 . 13) (100 . "AcDbLine") (10 7865.7607692308
1334.8416289593 0.0) (11 7714.9321266968 1334.8416289593 0.0))
((0 . "LINE") (100 . "AcDbEntity") (8 . "MASONRY") (62 . 7) (370 . 13) (100 . "AcDbLine") (10 7722.4745248869
1300.9049773756 0.0) (11 7714.9321266968 1300.9049773756 0.0))
((0 . "LINE") (100 . "AcDbEntity") (8 . "MASONRY") (62 . 7) (370 . 13) (100 . "AcDbLine") (10 7865.7607692308
3042.9864253394 0.0) (11 7733.7867420814 3042.9864253394 0.0))
((0 . "LINE") (100 . "AcDbEntity") (8 . "MASONRY") (62 . 7) (370 . 13) (100 . "AcDbLine") (10 7750.7536877828
1828.8086764706 0.0) (11 7750.7536877828 1847.6619117647 0.0))
((0 . "LINE") (100 . "AcDbEntity") (8 . "MASONRY") (62 . 7) (370 . 13) (100 . "AcDbLine") (10 7750.7536877828
1811.8396606335 0.0) (11 7741.3263800905 1811.8396606335 0.0))
((0 . "LINE") (100 . "AcDbEntity") (8 . "MASONRY") (62 . 7) (370 . 13) (100 . "AcDbLine") (10 7745.098959276
2400.0749547511 0.0) (11 7861.9909502262 2400.0749547511 0.0))
((0 . "LINE") (100 . "AcDbEntity") (8 . "MASONRY") (62 . 7) (370 . 13) (100 . "AcDbLine") (10 7812.9722624434
642.9114705882 0.0) (11 7745.098959276 642.9114705882 0.0))
((0 . "LINE") (100 . "AcDbEntity") (8 . "MASONRY") (62 . 7) (370 . 13) (100 . "AcDbLine") (10 7750.7536877828
1806.1849321267 0.0) (11 7750.7536877828 1811.8396606335 0.0))
((0 . "LINE") (100 . "AcDbEntity") (8 . "MASONRY") (62 . 7) (370 . 13) (100 . "AcDbLine") (10 7750.7536877828
1828.8086764706 0.0) (11 7750.7536877828 1811.8396606335 0.0))
((0 . "LINE") (100 . "AcDbEntity") (8 . "MASONRY") (62 . 7) (370 . 13) (100 . "AcDbLine") (10 7750.7536877828
1828.8086764706 0.0) (11 7775.2630316742 1828.8086764706 0.0))
((0 . "LINE") (100 . "AcDbEntity") (8 . "MASONRY") (62 . 7) (370 . 13) (100 . "AcDbLine") (10 7869.5333484163
1753.3936651584 0.0) (11 7752.6385972851 1753.3936651584 0.0))
((0 . "LINE") (100 . "AcDbEntity") (8 . "MASONRY") (62 . 7) (370 . 13) (100 . "AcDbLine") (10 7769.6069230769
2288.8383823529 0.0) (11 7769.6069230769 2266.2139479638 0.0))
((0 . "LINE") (100 . "AcDbEntity") (8 . "MASONRY") (62 . 7) (370 . 13) (100 . "AcDbLine") (10 7763.9508144796
1953.2430656109 0.0) (11 7861.9909502262 1953.2430656109 0.0))
((0 . "LINE") (100 . "AcDbEntity") (8 . "MASONRY") (62 . 7) (370 . 13) (100 . "AcDbLine") (10 7767.7220135747
573.1532579186 0.0) (11 7767.7220135747 561.841040724 0.0))
((0 . "LINE") (100 . "AcDbEntity") (8 . "MASONRY") (62 . 7) (370 . 13) (100 . "AcDbLine") (10 7779.0356108597
2188.9140271493 0.0) (11 7779.0356108597 2239.8190045249 0.0))
((0 . "LINE") (100 . "AcDbEntity") (8 . "MASONRY") (62 . 7) (370 . 13) (100 . "AcDbLine") (10 7869.5333484163
2188.9140271493 0.0) (11 7779.0356108597 2188.9140271493 0.0))
((0 . "LINE") (100 . "AcDbEntity") (8 . "MASONRY") (62 . 7) (370 . 13) (100 . "AcDbLine") (10 7794.1176470588
2846.9082239819 0.0) (11 7794.1176470588 2830.0165384615 0.0))
((0 . "LINE") (100 . "AcDbEntity") (8 . "MASONRY") (62 . 7) (370 . 13) (100 . "AcDbLine") (10 7794.1176470588
2830.0165384615 0.0) (11 7869.5333484163 2830.0165384615 0.0))
((0 . "LINE") (100 . "AcDbEntity") (8 . "MASONRY") (62 . 7) (370 . 13) (100 . "AcDbLine") (10 7797.8874660633
1830.6942760181 0.0) (11 7865.7607692308 1830.6942760181 0.0))
((0 . "LINE") (100 . "AcDbEntity") (8 . "MASONRY") (62 . 7) (370 . 13) (100 . "AcDbLine") (10 7822.3981900452
2586.7272285068 0.0) (11 7822.3981900452 2567.8733031674 0.0))
((0 . "LINE") (100 . "AcDbEntity") (8 . "MASONRY") (62 . 7) (370 . 13) (100 . "AcDbLine") (10 7820.5119004525
563.7259502262 0.0) (11 7858.2211312217 563.7259502262 0.0))
((0 . "LINE") (100 . "AcDbEntity") (8 . "MASONRY") (62 . 7) (370 . 13) (100 . "AcDbLine") (10 7861.9909502262
2586.7272285068 0.0) (11 7822.3981900452 2586.7272285068 0.0))
((0 . "LINE") (100 . "AcDbEntity") (8 . "MASONRY") (62 . 7) (370 . 13) (100 . "AcDbLine") (10 7846.9089140271
955.8823529412 0.0) (11 7861.9909502262 955.8823529412 0.0))
((0 . "LINE") (100 . "AcDbEntity") (8 . "MASONRY") (62 . 7) (370 . 13) (100 . "AcDbLine") (10 9592.7601809955
5539.2152262443 0.0) (11 9592.7601809955 5512.8209728507 0.0))
((0 . "LINE") (100 . "AcDbEntity") (8 . "MASONRY") (62 . 7) (370 . 13) (100 . "AcDbLine") (10 9884.9155882353
5248.8687782805 0.0) (11 9611.6147963801 5248.8687782805 0.0))
((0 . "LINE") (100 . "AcDbEntity") (8 . "MASONRY") (62 . 7) (370 . 13) (100 . "AcDbLine") (10 9611.6147963801
5248.8687782805 0.0) (11 9592.7601809955 5248.8687782805 0.0))
((0 . "LINE") (100 . "AcDbEntity") (8 . "MASONRY") (62 . 7) (370 . 13) (100 . "AcDbLine") (10 9715.3096606335
2771.4932126697 0.0) (11 9592.7601809955 2771.4932126697 0.0))
((0 . "LINE") (100 . "AcDbEntity") (8 . "MASONRY") (62 . 7) (370 . 13) (100 . "AcDbLine") (10 9753.0161312217
1987.1797171946 0.0) (11 9592.7601809955 1987.1797171946 0.0))
((0 . "LINE") (100 . "AcDbEntity") (8 . "MASONRY") (62 . 7) (370 . 13) (100 . "AcDbLine") (10 9792.6102714932
776.9264479638 0.0) (11 9758.6660294118 776.9264479638 0.0))
((0 . "LINE") (100 . "AcDbEntity") (8 . "MASONRY") (62 . 7) (370 . 13) (100 . "AcDbLine") (10 9758.6660294118
776.9264479638 0.0) (11 9592.7601809955 776.9264479638 0.0))
((0 . "LINE") (100 . "AcDbEntity") (8 . "MASONRY") (62 . 7) (370 . 13) (100 . "AcDbLine") (10 9592.7601809955
424.2081447964 0.0) (11 9856.7109954751 424.2081447964 0.0))
((0 . "LINE") (100 . "AcDbEntity") (8 . "MASONRY") (62 . 7) (370 . 13) (100 . "AcDbLine") (10 10005.6561085973
6391.4027149321 0.0) (11 9596.53 6391.4027149321 0.0))
((0 . "LINE") (100 . "AcDbEntity") (8 . "MASONRY") (62 . 7) (370 . 13) (100 . "AcDbLine") (10 9596.53 6202.8658823529
0.0) (11 9639.893959276 6202.8658823529 0.0))
((0 . "LINE") (100 . "AcDbEntity") (8 . "MASONRY") (62 . 7) (370 . 13) (100 . "AcDbLine") (10 9596.53 6104.7525565611
0.0) (11 9639.2918891403 6104.7525565611 0.0))
((0 . "LINE") (100 . "AcDbEntity") (8 . "MASONRY") (62 . 7) (370 . 13) (100 . "AcDbLine") (10 9639.2918891403
6104.7525565611 0.0) (11 9639.2918891403 6063.3484162896 0.0))
((0 . "LINE") (100 . "AcDbEntity") (8 . "MASONRY") (62 . 7) (370 . 13) (100 . "AcDbLine") (10 9596.53 6063.3484162896
0.0) (11 9639.2918891403 6063.3484162896 0.0))
((0 . "LINE") (100 . "AcDbEntity") (8 . "MASONRY") (62 . 7) (370 . 13) (100 . "AcDbLine") (10 9596.53 5953.9971040724
0.0) (11 9719.079479638 5953.9971040724 0.0))
((0 . "LINE") (100 . "AcDbEntity") (8 . "MASONRY") (62 . 7) (370 . 13) (100 . "AcDbLine") (10 9596.53 5793.7408031674
0.0) (11 9604.07239819 5793.7408031674 0.0))
((0 . "LINE") (100 . "AcDbEntity") (8 . "MASONRY") (62 . 7) (370 . 13) (100 . "AcDbLine") (10 9596.53 5109.3509728507
0.0) (11 9638.0090497738 5109.3509728507 0.0))
((0 . "LINE") (100 . "AcDbEntity") (8 . "MASONRY") (62 . 7) (370 . 13) (100 . "AcDbLine") (10 9615.3846153846
4775.6412556561 0.0) (11 9596.53 4775.6412556561 0.0))
((0 . "LINE") (100 . "AcDbEntity") (8 . "MASONRY") (62 . 7) (370 . 13) (100 . "AcDbLine") (10 9639.8953393665
3989.4414705882 0.0) (11 9596.53 3989.4414705882 0.0))
((0 . "LINE") (100 . "AcDbEntity") (8 . "MASONRY") (62 . 7) (370 . 13) (100 . "AcDbLine") (10 9596.53 3951.735 0.0) (11
9596.53 3959.2760180995 0.0))
((0 . "LINE") (100 . "AcDbEntity") (8 . "MASONRY") (62 . 7) (370 . 13) (100 . "AcDbLine") (10 9845.3987782805
3740.5726923077 0.0) (11 9596.53 3740.5726923077 0.0))
((0 . "LINE") (100 . "AcDbEntity") (8 . "MASONRY") (62 . 7) (370 . 13) (100 . "AcDbLine") (10 9630.4666515837
3555.8067081448 0.0) (11 9596.53 3555.8067081448 0.0))
((0 . "LINE") (100 . "AcDbEntity") (8 . "MASONRY") (62 . 7) (370 . 13) (100 . "AcDbLine") (10 9596.53 3472.850678733
0.0) (11 10111.2358823529 3472.850678733 0.0))
((0 . "LINE") (100 . "AcDbEntity") (8 . "MASONRY") (62 . 7) (370 . 13) (100 . "AcDbLine") (10 9596.53 3099.5475113122
0.0) (11 9860.4835746606 3099.5475113122 0.0))
((0 . "LINE") (100 . "AcDbEntity") (8 . "MASONRY") (62 . 7) (370 . 13) (100 . "AcDbLine") (10 9596.53 2518.8539253394
0.0) (11 9622.9270135747 2518.8539253394 0.0))
((0 . "LINE") (100 . "AcDbEntity") (8 . "MASONRY") (62 . 7) (370 . 13) (100 . "AcDbLine") (10 9607.8422171946
2454.7511312217 0.0) (11 9596.53 2454.7511312217 0.0))
((0 . "LINE") (100 . "AcDbEntity") (8 . "MASONRY") (62 . 7) (370 . 13) (100 . "AcDbLine") (10 9596.53 1262.5964366516
0.0) (11 9632.348800905 1262.5964366516 0.0))
((0 . "LINE") (100 . "AcDbEntity") (8 . "MASONRY") (62 . 7) (370 . 13) (100 . "AcDbLine") (10 9632.348800905
1262.5964366516 0.0) (11 9632.348800905 1240.5740723982 0.0))
((0 . "LINE") (100 . "AcDbEntity") (8 . "MASONRY") (62 . 7) (370 . 13) (100 . "AcDbLine") (10 9781.2966742081
354.4485520362 0.0) (11 9596.53 354.4485520362 0.0))
((0 . "LINE") (100 . "AcDbEntity") (8 . "MASONRY") (62 . 7) (370 . 13) (100 . "AcDbLine") (10 9638.0090497738
177.2256561086 0.0) (11 9596.53 177.2256561086 0.0))
((0 . "LINE") (100 . "AcDbEntity") (8 . "MASONRY") (62 . 7) (370 . 13) (100 . "AcDbLine") (10 9679.4880995475
5331.8248076923 0.0) (11 9600.3025791855 5331.8248076923 0.0))
((0 . "LINE") (100 . "AcDbEntity") (8 . "MASONRY") (62 . 7) (370 . 13) (100 . "AcDbLine") (10 9600.3025791855
5003.771199095 0.0) (11 9653.0910859729 5003.771199095 0.0))
((0 . "LINE") (100 . "AcDbEntity") (8 . "MASONRY") (62 . 7) (370 . 13) (100 . "AcDbLine") (10 9615.3846153846
4724.7355882353 0.0) (11 9600.3025791855 4724.7355882353 0.0))
((0 . "LINE") (100 . "AcDbEntity") (8 . "MASONRY") (62 . 7) (370 . 13) (100 . "AcDbLine") (10 9626.6968325792
4596.5313800905 0.0) (11 9600.3025791855 4596.5313800905 0.0))
((0 . "LINE") (100 . "AcDbEntity") (8 . "MASONRY") (62 . 7) (370 . 13) (100 . "AcDbLine") (10 9600.3025791855
4102.5636425339 0.0) (11 9600.3025791855 4096.9082239819 0.0))
((0 . "LINE") (100 . "AcDbEntity") (8 . "MASONRY") (62 . 7) (370 . 13) (100 . "AcDbLine") (10 9600.3025791855
4087.4816063348 0.0) (11 9600.3025791855 4096.9082239819 0.0))
((0 . "LINE") (100 . "AcDbEntity") (8 . "MASONRY") (62 . 7) (370 . 13) (100 . "AcDbLine") (10 9600.3025791855
4068.6269909502 0.0) (11 9717.1945701357 4068.6269909502 0.0))
((0 . "LINE") (100 . "AcDbEntity") (8 . "MASONRY") (62 . 7) (370 . 13) (100 . "AcDbLine") (10 9600.3025791855
3684.0116063348 0.0) (11 9630.4666515837 3684.0116063348 0.0))
((0 . "LINE") (100 . "AcDbEntity") (8 . "MASONRY") (62 . 7) (370 . 13) (100 . "AcDbLine") (10 9630.4666515837
3597.2850678733 0.0) (11 9600.3025791855 3597.2850678733 0.0))
((0 . "LINE") (100 . "AcDbEntity") (8 . "MASONRY") (62 . 7) (370 . 13) (100 . "AcDbLine") (10 9600.3025791855
3190.0452488688 0.0) (11 9862.3671040724 3190.0452488688 0.0))
((0 . "LINE") (100 . "AcDbEntity") (8 . "MASONRY") (62 . 7) (370 . 13) (100 . "AcDbLine") (10 9739.8190045249
2941.1764705882 0.0) (11 9600.3025791855 2941.1764705882 0.0))
((0 . "LINE") (100 . "AcDbEntity") (8 . "MASONRY") (62 . 7) (370 . 13) (100 . "AcDbLine") (10 9626.0947624434
2741.3270701357 0.0) (11 9626.0947624434 2720.5882352941 0.0))
((0 . "LINE") (100 . "AcDbEntity") (8 . "MASONRY") (62 . 7) (370 . 13) (100 . "AcDbLine") (10 9626.0947624434
2720.5882352941 0.0) (11 9600.3025791855 2720.5882352941 0.0))
((0 . "LINE") (100 . "AcDbEntity") (8 . "MASONRY") (62 . 7) (370 . 13) (100 . "AcDbLine") (10 9841.628959276
2405.7317533937 0.0) (11 9600.3025791855 2405.7317533937 0.0))
((0 . "LINE") (100 . "AcDbEntity") (8 . "MASONRY") (62 . 7) (370 . 13) (100 . "AcDbLine") (10 9600.3025791855
2313.3484162896 0.0) (11 9668.1758823529 2313.3484162896 0.0))
((0 . "LINE") (100 . "AcDbEntity") (8 . "MASONRY") (62 . 7) (370 . 13) (100 . "AcDbLine") (10 9687.0291176471
2237.9340950226 0.0) (11 9600.3025791855 2237.9340950226 0.0))
((0 . "LINE") (100 . "AcDbEntity") (8 . "MASONRY") (62 . 7) (370 . 13) (100 . "AcDbLine") (10 9653.0910859729
1858.9741289593 0.0) (11 9600.3025791855 1858.9741289593 0.0))
((0 . "LINE") (100 . "AcDbEntity") (8 . "MASONRY") (62 . 7) (370 . 13) (100 . "AcDbLine") (10 9600.3025791855
1613.877239819 0.0) (11 9719.079479638 1613.877239819 0.0))
((0 . "LINE") (100 . "AcDbEntity") (8 . "MASONRY") (62 . 7) (370 . 13) (100 . "AcDbLine") (10 9600.3025791855
1340.4977375566 0.0) (11 9694.5701357466 1340.4977375566 0.0))
((0 . "LINE") (100 . "AcDbEntity") (8 . "MASONRY") (62 . 7) (370 . 13) (100 . "AcDbLine") (10 9626.6968325792
1176.4705882353 0.0) (11 9600.3025791855 1176.4705882353 0.0))
((0 . "LINE") (100 . "AcDbEntity") (8 . "MASONRY") (62 . 7) (370 . 13) (100 . "AcDbLine") (10 9671.9457013575
991.7052941176 0.0) (11 9600.3025791855 991.7052941176 0.0))
((0 . "LINE") (100 . "AcDbEntity") (8 . "MASONRY") (62 . 7) (370 . 13) (100 . "AcDbLine") (10 9679.4880995475
852.1874886878 0.0) (11 9600.3025791855 852.1874886878 0.0))
((0 . "LINE") (100 . "AcDbEntity") (8 . "MASONRY") (62 . 7) (370 . 13) (100 . "AcDbLine") (10 9647.4363574661
720.212081448 0.0) (11 9600.3025791855 720.212081448 0.0))
((0 . "LINE") (100 . "AcDbEntity") (8 . "MASONRY") (62 . 7) (370 . 13) (100 . "AcDbLine") (10 9600.3025791855
595.7776923077 0.0) (11 9607.8422171946 595.7776923077 0.0))
((0 . "LINE") (100 . "AcDbEntity") (8 . "MASONRY") (62 . 7) (370 . 13) (100 . "AcDbLine") (10 9762.443438914
539.2166063348 0.0) (11 9600.3025791855 539.2166063348 0.0))
((0 . "LINE") (100 . "AcDbEntity") (8 . "MASONRY") (62 . 7) (370 . 13) (100 . "AcDbLine") (10 9600.3025791855
246.9838687783 0.0) (11 9607.8422171946 246.9838687783 0.0))
((0 . "LINE") (100 . "AcDbEntity") (8 . "MASONRY") (62 . 7) (370 . 13) (100 . "AcDbLine") (10 9894.4202262443
82.956719457 0.0) (11 9600.3025791855 82.956719457 0.0))
((0 . "LINE") (100 . "AcDbEntity") (8 . "MASONRY") (62 . 7) (370 . 13) (100 . "AcDbLine") (10 9622.9270135747
5712.6696832579 0.0) (11 9604.07239819 5712.6696832579 0.0))
((0 . "LINE") (100 . "AcDbEntity") (8 . "MASONRY") (62 . 7) (370 . 13) (100 . "AcDbLine") (10 9604.07239819
5678.7330316742 0.0) (11 9622.9270135747 5678.7330316742 0.0))
((0 . "LINE") (100 . "AcDbEntity") (8 . "MASONRY") (62 . 7) (370 . 13) (100 . "AcDbLine") (10 9604.07239819
5446.8325791855 0.0) (11 9664.4033031674 5446.8325791855 0.0))
((0 . "LINE") (100 . "AcDbEntity") (8 . "MASONRY") (62 . 7) (370 . 13) (100 . "AcDbLine") (10 9638.0090497738
5135.5919457014 0.0) (11 9604.07239819 5135.5919457014 0.0))
((0 . "LINE") (100 . "AcDbEntity") (8 . "MASONRY") (62 . 7) (370 . 13) (100 . "AcDbLine") (10 9798.2615497738
4892.5339366516 0.0) (11 9604.07239819 4892.5339366516 0.0))
((0 . "LINE") (100 . "AcDbEntity") (8 . "MASONRY") (62 . 7) (370 . 13) (100 . "AcDbLine") (10 10118.778280543
4517.3458597285 0.0) (11 9604.07239819 4517.3458597285 0.0))
((0 . "LINE") (100 . "AcDbEntity") (8 . "MASONRY") (62 . 7) (370 . 13) (100 . "AcDbLine") (10 9798.265 4411.7647058824
0.0) (11 9604.07239819 4411.7647058824 0.0))
((0 . "LINE") (100 . "AcDbEntity") (8 . "MASONRY") (62 . 7) (370 . 13) (100 . "AcDbLine") (10 9604.07239819
4340.0435633484 0.0) (11 9720.9595588235 4340.0435633484 0.0))
((0 . "LINE") (100 . "AcDbEntity") (8 . "MASONRY") (62 . 7) (370 . 13) (100 . "AcDbLine") (10 9720.9595588235
4340.0435633484 0.0) (11 9739.8190045249 4340.0435633484 0.0))
((0 . "LINE") (100 . "AcDbEntity") (8 . "MASONRY") (62 . 7) (370 . 13) (100 . "AcDbLine") (10 9739.8190045249
4340.0435633484 0.0) (11 9866.1383031674 4340.0435633484 0.0))
((0 . "LINE") (100 . "AcDbEntity") (8 . "MASONRY") (62 . 7) (370 . 13) (100 . "AcDbLine") (10 9866.1383031674
4193.0613800905 0.0) (11 9604.07239819 4193.0613800905 0.0))
((0 . "LINE") (100 . "AcDbEntity") (8 . "MASONRY") (62 . 7) (370 . 13) (100 . "AcDbLine") (10 9709.6521719457
4096.9082239819 0.0) (11 9600.3025791855 4096.9082239819 0.0))
((0 . "LINE") (100 . "AcDbEntity") (8 . "MASONRY") (62 . 7) (370 . 13) (100 . "AcDbLine") (10 9739.8190045249
3863.1221719457 0.0) (11 9604.07239819 3863.1221719457 0.0))
((0 . "LINE") (100 . "AcDbEntity") (8 . "MASONRY") (62 . 7) (370 . 13) (100 . "AcDbLine") (10 9604.07239819
3346.5313800905 0.0) (11 9683.257918552 3346.5313800905 0.0))
((0 . "LINE") (100 . "AcDbEntity") (8 . "MASONRY") (62 . 7) (370 . 13) (100 . "AcDbLine") (10 9606.0346380091
3291.8552036199 0.0) (11 9606.0346380091 3283.0341063348 0.0))
((0 . "LINE") (100 . "AcDbEntity") (8 . "MASONRY") (62 . 7) (370 . 13) (100 . "AcDbLine") (10 9606.0346380091
3283.0341063348 0.0) (11 9630.4666515837 3283.0341063348 0.0))
((0 . "LINE") (100 . "AcDbEntity") (8 . "MASONRY") (62 . 7) (370 . 13) (100 . "AcDbLine") (10 9604.07239819
3035.4447171946 0.0) (11 9786.9527828054 3035.4447171946 0.0))
((0 . "LINE") (100 . "AcDbEntity") (8 . "MASONRY") (62 . 7) (370 . 13) (100 . "AcDbLine") (10 9632.276300905
2631.9760972851 0.0) (11 9632.276300905 2603.7017647059 0.0))
((0 . "LINE") (100 . "AcDbEntity") (8 . "MASONRY") (62 . 7) (370 . 13) (100 . "AcDbLine") (10 9632.276300905
2603.7017647059 0.0) (11 9604.07239819 2603.7017647059 0.0))
((0 . "LINE") (100 . "AcDbEntity") (8 . "MASONRY") (62 . 7) (370 . 13) (100 . "AcDbLine") (10 9641.7788687783
2109.7285067873 0.0) (11 9604.07239819 2109.7285067873 0.0))
((0 . "LINE") (100 . "AcDbEntity") (8 . "MASONRY") (62 . 7) (370 . 13) (100 . "AcDbLine") (10 9785.0678733032
1738.3116289593 0.0) (11 9604.07239819 1738.3116289593 0.0))
((0 . "LINE") (100 . "AcDbEntity") (8 . "MASONRY") (62 . 7) (370 . 13) (100 . "AcDbLine") (10 9604.07239819
1527.149321267 0.0) (11 9777.5254751131 1527.149321267 0.0))
((0 . "LINE") (100 . "AcDbEntity") (8 . "MASONRY") (62 . 7) (370 . 13) (100 . "AcDbLine") (10 9604.07239819
1436.6515837104 0.0) (11 9981.1453846154 1436.6515837104 0.0))
((0 . "LINE") (100 . "AcDbEntity") (8 . "MASONRY") (62 . 7) (370 . 13) (100 . "AcDbLine") (10 9604.07239819
1089.7426696833 0.0) (11 9658.7471945701 1089.7426696833 0.0))
((0 . "LINE") (100 . "AcDbEntity") (8 . "MASONRY") (62 . 7) (370 . 13) (100 . "AcDbLine") (10 9615.3846153846
4785.0678733032 0.0) (11 9615.3846153846 4837.857760181 0.0))
((0 . "LINE") (100 . "AcDbEntity") (8 . "MASONRY") (62 . 7) (370 . 13) (100 . "AcDbLine") (10 9615.3846153846
4775.6412556561 0.0) (11 9615.3846153846 4724.7355882353 0.0))
((0 . "LINE") (100 . "AcDbEntity") (8 . "MASONRY") (62 . 7) (370 . 13) (100 . "AcDbLine") (10 9615.3846153846
4785.0678733032 0.0) (11 9615.3846153846 4775.6412556561 0.0))
((0 . "LINE") (100 . "AcDbEntity") (8 . "MASONRY") (62 . 7) (370 . 13) (100 . "AcDbLine") (10 9613.5031561086
4291.1015158371 0.0) (11 9613.5031561086 4272.3242307692 0.0))
((0 . "LINE") (100 . "AcDbEntity") (8 . "MASONRY") (62 . 7) (370 . 13) (100 . "AcDbLine") (10 9613.5031561086
4272.3242307692 0.0) (11 9819.0045248869 4272.3242307692 0.0))
((0 . "LINE") (100 . "AcDbEntity") (8 . "MASONRY") (62 . 7) (370 . 13) (100 . "AcDbLine") (10 9615.3846153846
2631.9760972851 0.0) (11 9632.276300905 2631.9760972851 0.0))
((0 . "LINE") (100 . "AcDbEntity") (8 . "MASONRY") (62 . 7) (370 . 13) (100 . "AcDbLine") (10 9619.1544343891
5840.8749321267 0.0) (11 9634.2392307692 5840.8749321267 0.0))
((0 . "LINE") (100 . "AcDbEntity") (8 . "MASONRY") (62 . 7) (370 . 13) (100 . "AcDbLine") (10 9615.3846153846
4785.0678733032 0.0) (11 9871.7957918552 4785.0678733032 0.0))
((0 . "LINE") (100 . "AcDbEntity") (8 . "MASONRY") (62 . 7) (370 . 13) (100 . "AcDbLine") (10 9871.7957918552
4785.0678733032 0.0) (11 9949.0950226244 4785.0678733032 0.0))
((0 . "LINE") (100 . "AcDbEntity") (8 . "MASONRY") (62 . 7) (370 . 13) (100 . "AcDbLine") (10 9615.3846153846
4724.7355882353 0.0) (11 9671.9457013575 4724.7355882353 0.0))
((0 . "LINE") (100 . "AcDbEntity") (8 . "MASONRY") (62 . 7) (370 . 13) (100 . "AcDbLine") (10 9622.9270135747
5712.6696832579 0.0) (11 9622.9270135747 5678.7330316742 0.0))
((0 . "LINE") (100 . "AcDbEntity") (8 . "MASONRY") (62 . 7) (370 . 13) (100 . "AcDbLine") (10 9634.2392307692
5712.6696832579 0.0) (11 9622.9270135747 5712.6696832579 0.0))
((0 . "LINE") (100 . "AcDbEntity") (8 . "MASONRY") (62 . 7) (370 . 13) (100 . "AcDbLine") (10 9961.0093099548
5678.7330316742 0.0) (11 9622.9270135747 5678.7330316742 0.0))
((0 . "LINE") (100 . "AcDbEntity") (8 . "MASONRY") (62 . 7) (370 . 13) (100 . "AcDbLine") (10 9622.9270135747
2564.1027941176 0.0) (11 9622.9270135747 2518.8539253394 0.0))
((0 . "LINE") (100 . "AcDbEntity") (8 . "MASONRY") (62 . 7) (370 . 13) (100 . "AcDbLine") (10 9653.0910859729
2518.8539253394 0.0) (11 9622.9270135747 2518.8539253394 0.0))
((0 . "LINE") (100 . "AcDbEntity") (8 . "MASONRY") (62 . 7) (370 . 13) (100 . "AcDbLine") (10 9626.6968325792
5791.8552036199 0.0) (11 9638.0090497738 5791.8552036199 0.0))
((0 . "LINE") (100 . "AcDbEntity") (8 . "MASONRY") (62 . 7) (370 . 13) (100 . "AcDbLine") (10 9626.6968325792
5607.0885294118 0.0) (11 9626.6968325792 5641.025520362 0.0))
((0 . "LINE") (100 . "AcDbEntity") (8 . "MASONRY") (62 . 7) (370 . 13) (100 . "AcDbLine") (10 9660.6334841629
5554.9007126697 0.0) (11 9628.6590723982 5554.9007126697 0.0))
((0 . "LINE") (100 . "AcDbEntity") (8 . "MASONRY") (62 . 7) (370 . 13) (100 . "AcDbLine") (10 9628.6590723982
5554.9007126697 0.0) (11 9628.6590723982 5569.3820588235 0.0))
((0 . "LINE") (100 . "AcDbEntity") (8 . "MASONRY") (62 . 7) (370 . 13) (100 . "AcDbLine") (10 9626.6968325792
1176.4705882353 0.0) (11 9626.6968325792 1142.5339366516 0.0))
((0 . "LINE") (100 . "AcDbEntity") (8 . "MASONRY") (62 . 7) (370 . 13) (100 . "AcDbLine") (10 9626.6968325792
1176.4705882353 0.0) (11 9920.814479638 1176.4705882353 0.0))
((0 . "LINE") (100 . "AcDbEntity") (8 . "MASONRY") (62 . 7) (370 . 13) (100 . "AcDbLine") (10 9638.0090497738
6340.4977375566 0.0) (11 9630.4666515837 6340.4977375566 0.0))
((0 . "LINE") (100 . "AcDbEntity") (8 . "MASONRY") (62 . 7) (370 . 13) (100 . "AcDbLine") (10 9630.4666515837
3684.0116063348 0.0) (11 9630.4666515837 3627.450520362 0.0))
((0 . "LINE") (100 . "AcDbEntity") (8 . "MASONRY") (62 . 7) (370 . 13) (100 . "AcDbLine") (10 9732.2766063348
3684.0116063348 0.0) (11 9630.4666515837 3684.0116063348 0.0))
((0 . "LINE") (100 . "AcDbEntity") (8 . "MASONRY") (62 . 7) (370 . 13) (100 . "AcDbLine") (10 9630.4666515837
3597.2850678733 0.0) (11 9754.901040724 3597.2850678733 0.0))
((0 . "LINE") (100 . "AcDbEntity") (8 . "MASONRY") (62 . 7) (370 . 13) (100 . "AcDbLine") (10 9630.4666515837
3597.2850678733 0.0) (11 9630.4666515837 3555.8067081448 0.0))
((0 . "LINE") (100 . "AcDbEntity") (8 . "MASONRY") (62 . 7) (370 . 13) (100 . "AcDbLine") (10 9702.1125339367
3555.8067081448 0.0) (11 9630.4666515837 3555.8067081448 0.0))
((0 . "LINE") (100 . "AcDbEntity") (8 . "MASONRY") (62 . 7) (370 . 13) (100 . "AcDbLine") (10 9630.4666515837
1672.3232352941 0.0) (11 9641.7788687783 1672.3232352941 0.0))
((0 . "LINE") (100 . "AcDbEntity") (8 . "MASONRY") (62 . 7) (370 . 13) (100 . "AcDbLine") (10 9634.2392307692
5519.0784615385 0.0) (11 9794.2362669683 5519.0784615385 0.0))
((0 . "LINE") (100 . "AcDbEntity") (8 . "MASONRY") (62 . 7) (370 . 13) (100 . "AcDbLine") (10 9794.2362669683
5519.0784615385 0.0) (11 9794.2362669683 5558.069841629 0.0))
((0 . "LINE") (100 . "AcDbEntity") (8 . "MASONRY") (62 . 7) (370 . 13) (100 . "AcDbLine") (10 9639.8953393665
3989.4414705882 0.0) (11 9639.8953393665 3955.5048190045 0.0))
((0 . "LINE") (100 . "AcDbEntity") (8 . "MASONRY") (62 . 7) (370 . 13) (100 . "AcDbLine") (10 9845.3987782805
2631.9760972851 0.0) (11 9632.276300905 2631.9760972851 0.0))
((0 . "LINE") (100 . "AcDbEntity") (8 . "MASONRY") (62 . 7) (370 . 13) (100 . "AcDbLine") (10 9638.0090497738
6255.6561085973 0.0) (11 9773.7556561086 6255.6561085973 0.0))
((0 . "LINE") (100 . "AcDbEntity") (8 . "MASONRY") (62 . 7) (370 . 13) (100 . "AcDbLine") (10 9639.893959276
6202.8658823529 0.0) (11 9736.0491855204 6202.8658823529 0.0))
((0 . "LINE") (100 . "AcDbEntity") (8 . "MASONRY") (62 . 7) (370 . 13) (100 . "AcDbLine") (10 9639.893959276
6221.7194570136 0.0) (11 9639.893959276 6202.8658823529 0.0))
((0 . "LINE") (100 . "AcDbEntity") (8 . "MASONRY") (62 . 7) (370 . 13) (100 . "AcDbLine") (10 9732.2779864253
6063.3484162896 0.0) (11 9639.2918891403 6063.3484162896 0.0))
((0 . "LINE") (100 . "AcDbEntity") (8 . "MASONRY") (62 . 7) (370 . 13) (100 . "AcDbLine") (10 9638.0090497738
5742.8354751131 0.0) (11 9638.0090497738 5791.8552036199 0.0))
((0 . "LINE") (100 . "AcDbEntity") (8 . "MASONRY") (62 . 7) (370 . 13) (100 . "AcDbLine") (10 9782.6547737557
5791.8552036199 0.0) (11 9638.0090497738 5791.8552036199 0.0))
((0 . "LINE") (100 . "AcDbEntity") (8 . "MASONRY") (62 . 7) (370 . 13) (100 . "AcDbLine") (10 9638.0090497738
5135.5919457014 0.0) (11 9638.0090497738 5109.3509728507 0.0))
((0 . "LINE") (100 . "AcDbEntity") (8 . "MASONRY") (62 . 7) (370 . 13) (100 . "AcDbLine") (10 9638.0090497738
5135.5919457014 0.0) (11 9785.0678733032 5135.5919457014 0.0))
((0 . "LINE") (100 . "AcDbEntity") (8 . "MASONRY") (62 . 7) (370 . 13) (100 . "AcDbLine") (10 9785.0678733032
5109.3509728507 0.0) (11 9638.0090497738 5109.3509728507 0.0))
((0 . "LINE") (100 . "AcDbEntity") (8 . "MASONRY") (62 . 7) (370 . 13) (100 . "AcDbLine") (10 9638.0090497738
218.7019457014 0.0) (11 9638.0090497738 177.2256561086 0.0))
((0 . "LINE") (100 . "AcDbEntity") (8 . "MASONRY") (62 . 7) (370 . 13) (100 . "AcDbLine") (10 9638.0090497738
177.2256561086 0.0) (11 9809.5772171946 177.2256561086 0.0))
((0 . "LINE") (100 . "AcDbEntity") (8 . "MASONRY") (62 . 7) (370 . 13) (100 . "AcDbLine") (10 9773.7556561086
6297.2887782805 0.0) (11 9643.667918552 6297.2887782805 0.0))
((0 . "LINE") (100 . "AcDbEntity") (8 . "MASONRY") (62 . 7) (370 . 13) (100 . "AcDbLine") (10 9643.667918552
6297.2887782805 0.0) (11 9643.667918552 6312.2171945701 0.0))
((0 . "LINE") (100 . "AcDbEntity") (8 . "MASONRY") (62 . 7) (370 . 13) (100 . "AcDbLine") (10 9641.7788687783
2458.5216402715 0.0) (11 9653.0910859729 2458.5216402715 0.0))
((0 . "LINE") (100 . "AcDbEntity") (8 . "MASONRY") (62 . 7) (370 . 13) (100 . "AcDbLine") (10 9641.7788687783
309.1996832579 0.0) (11 9649.3212669683 309.1996832579 0.0))
((0 . "LINE") (100 . "AcDbEntity") (8 . "MASONRY") (62 . 7) (370 . 13) (100 . "AcDbLine") (10 9649.3212669683
248.8687782805 0.0) (11 9649.3212669683 260.1809954751 0.0))
((0 . "LINE") (100 . "AcDbEntity") (8 . "MASONRY") (62 . 7) (370 . 13) (100 . "AcDbLine") (10 9798.2615497738
4892.5339366516 0.0) (11 9798.2615497738 4937.7058257919 0.0))
((0 . "LINE") (100 . "AcDbEntity") (8 . "MASONRY") (62 . 7) (370 . 13) (100 . "AcDbLine") (10 9798.2615497738
4937.7058257919 0.0) (11 9645.5514479638 4937.7058257919 0.0))
((0 . "LINE") (100 . "AcDbEntity") (8 . "MASONRY") (62 . 7) (370 . 13) (100 . "AcDbLine") (10 9639.8953393665
3989.4414705882 0.0) (11 9656.8636651584 3989.4414705882 0.0))
((0 . "LINE") (100 . "AcDbEntity") (8 . "MASONRY") (62 . 7) (370 . 13) (100 . "AcDbLine") (10 9645.5514479638
3286.1990950226 0.0) (11 9830.3167420814 3286.1990950226 0.0))
((0 . "LINE") (100 . "AcDbEntity") (8 . "MASONRY") (62 . 7) (370 . 13) (100 . "AcDbLine") (10 9647.4363574661
663.6509954751 0.0) (11 9647.4363574661 720.212081448 0.0))
((0 . "LINE") (100 . "AcDbEntity") (8 . "MASONRY") (62 . 7) (370 . 13) (100 . "AcDbLine") (10 10388.3852036199
720.212081448 0.0) (11 9647.4363574661 720.212081448 0.0))
((0 . "LINE") (100 . "AcDbEntity") (8 . "MASONRY") (62 . 7) (370 . 13) (100 . "AcDbLine") (10 9739.8190045249
3917.720678733 0.0) (11 9649.3212669683 3917.720678733 0.0))
((0 . "LINE") (100 . "AcDbEntity") (8 . "MASONRY") (62 . 7) (370 . 13) (100 . "AcDbLine") (10 9649.3212669683
580.6928959276 0.0) (11 9649.3212669683 629.7143438914 0.0))
((0 . "LINE") (100 . "AcDbEntity") (8 . "MASONRY") (62 . 7) (370 . 13) (100 . "AcDbLine") (10 9649.3212669683
271.4932126697 0.0) (11 9649.3212669683 260.1809954751 0.0))
((0 . "LINE") (100 . "AcDbEntity") (8 . "MASONRY") (62 . 7) (370 . 13) (100 . "AcDbLine") (10 9724.7369683258
260.1809954751 0.0) (11 9649.3212669683 260.1809954751 0.0))
((0 . "LINE") (100 . "AcDbEntity") (8 . "MASONRY") (62 . 7) (370 . 13) (100 . "AcDbLine") (10 9679.4880995475
6112.3681447964 0.0) (11 9653.0910859729 6112.3681447964 0.0))
((0 . "LINE") (100 . "AcDbEntity") (8 . "MASONRY") (62 . 7) (370 . 13) (100 . "AcDbLine") (10 9653.0910859729
4977.3755656109 0.0) (11 9653.0910859729 5003.771199095 0.0))
((0 . "LINE") (100 . "AcDbEntity") (8 . "MASONRY") (62 . 7) (370 . 13) (100 . "AcDbLine") (10 9653.0910859729
5003.771199095 0.0) (11 9785.2156334842 5003.771199095 0.0))
((0 . "LINE") (100 . "AcDbEntity") (8 . "MASONRY") (62 . 7) (370 . 13) (100 . "AcDbLine") (10 9785.2156334842
5003.771199095 0.0) (11 9785.2156334842 5064.1021040724 0.0))
((0 . "LINE") (100 . "AcDbEntity") (8 . "MASONRY") (62 . 7) (370 . 13) (100 . "AcDbLine") (10 9653.0910859729
2518.8539253394 0.0) (11 9653.0910859729 2458.5216402715 0.0))
((0 . "LINE") (100 . "AcDbEntity") (8 . "MASONRY") (62 . 7) (370 . 13) (100 . "AcDbLine") (10 10033.9366515837
2518.8539253394 0.0) (11 9653.0910859729 2518.8539253394 0.0))
((0 . "LINE") (100 . "AcDbEntity") (8 . "MASONRY") (62 . 7) (370 . 13) (100 . "AcDbLine") (10 9879.3354298643
2458.5216402715 0.0) (11 9653.0910859729 2458.5216402715 0.0))
((0 . "LINE") (100 . "AcDbEntity") (8 . "MASONRY") (62 . 7) (370 . 13) (100 . "AcDbLine") (10 9653.0910859729
1858.9741289593 0.0) (11 9653.0910859729 1885.3697624434 0.0))
((0 . "LINE") (100 . "AcDbEntity") (8 . "MASONRY") (62 . 7) (370 . 13) (100 . "AcDbLine") (10 9653.0910859729
1858.9741289593 0.0) (11 9736.0491855204 1858.9741289593 0.0))
((0 . "LINE") (100 . "AcDbEntity") (8 . "MASONRY") (62 . 7) (370 . 13) (100 . "AcDbLine") (10 9658.7471945701
1040.7239819005 0.0) (11 9658.7471945701 1089.7426696833 0.0))
((0 . "LINE") (100 . "AcDbEntity") (8 . "MASONRY") (62 . 7) (370 . 13) (100 . "AcDbLine") (10 9664.4033031674
1938.1596493213 0.0) (11 9664.4033031674 1945.7013574661 0.0))
((0 . "LINE") (100 . "AcDbEntity") (8 . "MASONRY") (62 . 7) (370 . 13) (100 . "AcDbLine") (10 9700.3028846154
1240.5740723982 0.0) (11 9664.4033031674 1240.5740723982 0.0))
((0 . "LINE") (100 . "AcDbEntity") (8 . "MASONRY") (62 . 7) (370 . 13) (100 . "AcDbLine") (10 9658.7471945701
1089.7426696833 0.0) (11 9683.257918552 1089.7426696833 0.0))
((0 . "LINE") (100 . "AcDbEntity") (8 . "MASONRY") (62 . 7) (370 . 13) (100 . "AcDbLine") (10 9668.1758823529
4626.6968325792 0.0) (11 9683.257918552 4626.6968325792 0.0))
((0 . "LINE") (100 . "AcDbEntity") (8 . "MASONRY") (62 . 7) (370 . 13) (100 . "AcDbLine") (10 9702.1125339367
2109.7285067873 0.0) (11 9668.1758823529 2109.7285067873 0.0))
((0 . "LINE") (100 . "AcDbEntity") (8 . "MASONRY") (62 . 7) (370 . 13) (100 . "AcDbLine") (10 9671.9457013575
4709.6535520362 0.0) (11 9671.9457013575 4724.7355882353 0.0))
((0 . "LINE") (100 . "AcDbEntity") (8 . "MASONRY") (62 . 7) (370 . 13) (100 . "AcDbLine") (10 9671.9457013575
4724.7355882353 0.0) (11 9950.9813122172 4724.7355882353 0.0))
((0 . "LINE") (100 . "AcDbEntity") (8 . "MASONRY") (62 . 7) (370 . 13) (100 . "AcDbLine") (10 9673.8306108597
4690.7989366516 0.0) (11 9673.8306108597 4668.1745022624 0.0))
((0 . "LINE") (100 . "AcDbEntity") (8 . "MASONRY") (62 . 7) (370 . 13) (100 . "AcDbLine") (10 9671.9457013575
991.7052941176 0.0) (11 9671.9457013575 961.5384615385 0.0))
((0 . "LINE") (100 . "AcDbEntity") (8 . "MASONRY") (62 . 7) (370 . 13) (100 . "AcDbLine") (10 9671.9457013575
991.7052941176 0.0) (11 9800.1512895928 991.7052941176 0.0))
((0 . "LINE") (100 . "AcDbEntity") (8 . "MASONRY") (62 . 7) (370 . 13) (100 . "AcDbLine") (10 9675.715520362
5556.1842420814 0.0) (11 9739.8190045249 5556.1842420814 0.0))
((0 . "LINE") (100 . "AcDbEntity") (8 . "MASONRY") (62 . 7) (370 . 13) (100 . "AcDbLine") (10 9675.715520362
3989.4414705882 0.0) (11 9888.7627375566 3989.4414705882 0.0))
((0 . "LINE") (100 . "AcDbEntity") (8 . "MASONRY") (62 . 7) (370 . 13) (100 . "AcDbLine") (10 9675.715520362
2601.8099547511 0.0) (11 9717.1945701357 2601.8099547511 0.0))
((0 . "LINE") (100 . "AcDbEntity") (8 . "MASONRY") (62 . 7) (370 . 13) (100 . "AcDbLine") (10 9675.715520362
1676.0930542986 0.0) (11 9743.5888235294 1676.0930542986 0.0))
((0 . "LINE") (100 . "AcDbEntity") (8 . "MASONRY") (62 . 7) (370 . 13) (100 . "AcDbLine") (10 9679.4880995475
5833.3332126697 0.0) (11 9782.6547737557 5833.3332126697 0.0))
((0 . "LINE") (100 . "AcDbEntity") (8 . "MASONRY") (62 . 7) (370 . 13) (100 . "AcDbLine") (10 9679.4880995475
916.2122624434 0.0) (11 9794.493800905 916.2122624434 0.0))
((0 . "LINE") (100 . "AcDbEntity") (8 . "MASONRY") (62 . 7) (370 . 13) (100 . "AcDbLine") (10 9794.493800905
916.2122624434 0.0) (11 9794.493800905 901.2075565611 0.0))
((0 . "LINE") (100 . "AcDbEntity") (8 . "MASONRY") (62 . 7) (370 . 13) (100 . "AcDbLine") (10 9687.0291176471
2237.9340950226 0.0) (11 9811.4621266968 2237.9340950226 0.0))
((0 . "LINE") (100 . "AcDbEntity") (8 . "MASONRY") (62 . 7) (370 . 13) (100 . "AcDbLine") (10 9687.0291176471
2237.9340950226 0.0) (11 9687.0291176471 2266.2139479638 0.0))
((0 . "LINE") (100 . "AcDbEntity") (8 . "MASONRY") (62 . 7) (370 . 13) (100 . "AcDbLine") (10 9687.0277375566
1936.2740497738 0.0) (11 9698.3399547511 1936.2740497738 0.0))
((0 . "LINE") (100 . "AcDbEntity") (8 . "MASONRY") (62 . 7) (370 . 13) (100 . "AcDbLine") (10 9690.8003167421
6106.7120361991 0.0) (11 9717.1945701357 6106.7120361991 0.0))
((0 . "LINE") (100 . "AcDbEntity") (8 . "MASONRY") (62 . 7) (370 . 13) (100 . "AcDbLine") (10 9717.1945701357
6106.7120361991 0.0) (11 9732.2779864253 6106.7120361991 0.0))
((0 . "LINE") (100 . "AcDbEntity") (8 . "MASONRY") (62 . 7) (370 . 13) (100 . "AcDbLine") (10 9694.5701357466
5439.2908710407 0.0) (11 9788.8363122172 5439.2908710407 0.0))
((0 . "LINE") (100 . "AcDbEntity") (8 . "MASONRY") (62 . 7) (370 . 13) (100 . "AcDbLine") (10 9854.8274660633
4611.6134162896 0.0) (11 9854.8274660633 4624.7339027149 0.0))
((0 . "LINE") (100 . "AcDbEntity") (8 . "MASONRY") (62 . 7) (370 . 13) (100 . "AcDbLine") (10 9854.8274660633
4624.7339027149 0.0) (11 9698.3399547511 4624.7339027149 0.0))
((0 . "LINE") (100 . "AcDbEntity") (8 . "MASONRY") (62 . 7) (370 . 13) (100 . "AcDbLine") (10 9700.3028846154
1240.5740723982 0.0) (11 9715.3096606335 1240.5740723982 0.0))
((0 . "LINE") (100 . "AcDbEntity") (8 . "MASONRY") (62 . 7) (370 . 13) (100 . "AcDbLine") (10 9700.3028846154
1240.5740723982 0.0) (11 9700.3028846154 1258.2155769231 0.0))
((0 . "LINE") (100 . "AcDbEntity") (8 . "MASONRY") (62 . 7) (370 . 13) (100 . "AcDbLine") (10 9700.3028846154
1258.2155769231 0.0) (11 9715.3096606335 1258.2155769231 0.0))
((0 . "LINE") (100 . "AcDbEntity") (8 . "MASONRY") (62 . 7) (370 . 13) (100 . "AcDbLine") (10 9705.8823529412
5346.9075339367 0.0) (11 9705.8823529412 5335.5953167421 0.0))
((0 . "LINE") (100 . "AcDbEntity") (8 . "MASONRY") (62 . 7) (370 . 13) (100 . "AcDbLine") (10 9788.8363122172
5439.2908710407 0.0) (11 9788.8363122172 5392.7591628959 0.0))
((0 . "LINE") (100 . "AcDbEntity") (8 . "MASONRY") (62 . 7) (370 . 13) (100 . "AcDbLine") (10 9788.8363122172
5392.7591628959 0.0) (11 9709.6521719457 5392.7591628959 0.0))
((0 . "LINE") (100 . "AcDbEntity") (8 . "MASONRY") (62 . 7) (370 . 13) (100 . "AcDbLine") (10 9883.1080090498
2833.7104072398 0.0) (11 9709.6521719457 2833.7104072398 0.0))
((0 . "LINE") (100 . "AcDbEntity") (8 . "MASONRY") (62 . 7) (370 . 13) (100 . "AcDbLine") (10 9715.3096606335
2771.4932126697 0.0) (11 9837.8591402715 2771.4932126697 0.0))
((0 . "LINE") (100 . "AcDbEntity") (8 . "MASONRY") (62 . 7) (370 . 13) (100 . "AcDbLine") (10 9715.3096606335
2771.4932126697 0.0) (11 9715.3096606335 2801.6593552036 0.0))
((0 . "LINE") (100 . "AcDbEntity") (8 . "MASONRY") (62 . 7) (370 . 13) (100 . "AcDbLine") (10 9732.2766063348
1240.5740723982 0.0) (11 9715.3096606335 1240.5740723982 0.0))
((0 . "LINE") (100 . "AcDbEntity") (8 . "MASONRY") (62 . 7) (370 . 13) (100 . "AcDbLine") (10 9715.3096606335
1258.2155769231 0.0) (11 9715.3096606335 1240.5740723982 0.0))
((0 . "LINE") (100 . "AcDbEntity") (8 . "MASONRY") (62 . 7) (370 . 13) (100 . "AcDbLine") (10 9719.079479638
5976.6215384615 0.0) (11 9719.079479638 5953.9971040724 0.0))
((0 . "LINE") (100 . "AcDbEntity") (8 . "MASONRY") (62 . 7) (370 . 13) (100 . "AcDbLine") (10 9717.1945701357
2911.0103280543 0.0) (11 9717.1945701357 2880.8448755656 0.0))
((0 . "LINE") (100 . "AcDbEntity") (8 . "MASONRY") (62 . 7) (370 . 13) (100 . "AcDbLine") (10 9728.5067873303
1613.877239819 0.0) (11 9719.079479638 1613.877239819 0.0))
((0 . "LINE") (100 . "AcDbEntity") (8 . "MASONRY") (62 . 7) (370 . 13) (100 . "AcDbLine") (10 9719.079479638
1628.9592760181 0.0) (11 9719.079479638 1613.877239819 0.0))
((0 . "LINE") (100 . "AcDbEntity") (8 . "MASONRY") (62 . 7) (370 . 13) (100 . "AcDbLine") (10 9732.2766063348
1258.2155769231 0.0) (11 9715.3096606335 1258.2155769231 0.0))
((0 . "LINE") (100 . "AcDbEntity") (8 . "MASONRY") (62 . 7) (370 . 13) (100 . "AcDbLine") (10 10039.592760181
5953.9971040724 0.0) (11 9719.079479638 5953.9971040724 0.0))
((0 . "LINE") (100 . "AcDbEntity") (8 . "MASONRY") (62 . 7) (370 . 13) (100 . "AcDbLine") (10 9720.9643891403
852.1874886878 0.0) (11 9751.1312217195 852.1874886878 0.0))
((0 . "LINE") (100 . "AcDbEntity") (8 . "MASONRY") (62 . 7) (370 . 13) (100 . "AcDbLine") (10 9743.4051696833
3352.1867986425 0.0) (11 9743.4051696833 3337.7061425339 0.0))
((0 . "LINE") (100 . "AcDbEntity") (8 . "MASONRY") (62 . 7) (370 . 13) (100 . "AcDbLine") (10 9743.4051696833
3337.7061425339 0.0) (11 9724.7369683258 3337.7061425339 0.0))
((0 . "LINE") (100 . "AcDbEntity") (8 . "MASONRY") (62 . 7) (370 . 13) (100 . "AcDbLine") (10 9852.9411764706
6063.3484162896 0.0) (11 9732.2779864253 6063.3484162896 0.0))
((0 . "LINE") (100 . "AcDbEntity") (8 . "MASONRY") (62 . 7) (370 . 13) (100 . "AcDbLine") (10 9732.2779864253
6106.7120361991 0.0) (11 9732.2779864253 6063.3484162896 0.0))
((0 . "LINE") (100 . "AcDbEntity") (8 . "MASONRY") (62 . 7) (370 . 13) (100 . "AcDbLine") (10 9796.3800904977
2269.9851470588 0.0) (11 9728.5067873303 2269.9851470588 0.0))
((0 . "LINE") (100 . "AcDbEntity") (8 . "MASONRY") (62 . 7) (370 . 13) (100 . "AcDbLine") (10 9728.5067873303
1340.4977375566 0.0) (11 9769.9858371041 1340.4977375566 0.0))
((0 . "LINE") (100 . "AcDbEntity") (8 . "MASONRY") (62 . 7) (370 . 13) (100 . "AcDbLine") (10 9971.7194570136
6014.3286877828 0.0) (11 9732.2766063348 6014.3286877828 0.0))
((0 . "LINE") (100 . "AcDbEntity") (8 . "MASONRY") (62 . 7) (370 . 13) (100 . "AcDbLine") (10 9732.2766063348
4470.2113914027 0.0) (11 9747.3614027149 4470.2113914027 0.0))
((0 . "LINE") (100 . "AcDbEntity") (8 . "MASONRY") (62 . 7) (370 . 13) (100 . "AcDbLine") (10 9743.5888235294
6106.7120361991 0.0) (11 9732.2779864253 6106.7120361991 0.0))
((0 . "LINE") (100 . "AcDbEntity") (8 . "MASONRY") (62 . 7) (370 . 13) (100 . "AcDbLine") (10 9736.0491855204
4068.6269909502 0.0) (11 9754.901040724 4068.6269909502 0.0))
((0 . "LINE") (100 . "AcDbEntity") (8 . "MASONRY") (62 . 7) (370 . 13) (100 . "AcDbLine") (10 9739.8190045249
3863.1221719457 0.0) (11 9739.8190045249 3917.720678733 0.0))
((0 . "LINE") (100 . "AcDbEntity") (8 . "MASONRY") (62 . 7) (370 . 13) (100 . "AcDbLine") (10 9890.6476470588
3917.720678733 0.0) (11 9754.901040724 3917.720678733 0.0))
((0 . "LINE") (100 . "AcDbEntity") (8 . "MASONRY") (62 . 7) (370 . 13) (100 . "AcDbLine") (10 9754.901040724
3917.720678733 0.0) (11 9739.8190045249 3917.720678733 0.0))
((0 . "LINE") (100 . "AcDbEntity") (8 . "MASONRY") (62 . 7) (370 . 13) (100 . "AcDbLine") (10 9888.7627375566
3863.1221719457 0.0) (11 9739.8190045249 3863.1221719457 0.0))
((0 . "LINE") (100 . "AcDbEntity") (8 . "MASONRY") (62 . 7) (370 . 13) (100 . "AcDbLine") (10 9743.5888235294
1700.60239819 0.0) (11 9743.5888235294 1676.0930542986 0.0))
((0 . "LINE") (100 . "AcDbEntity") (8 . "MASONRY") (62 . 7) (370 . 13) (100 . "AcDbLine") (10 10128.2042081448
1676.0930542986 0.0) (11 9743.5888235294 1676.0930542986 0.0))
((0 . "LINE") (100 . "AcDbEntity") (8 . "MASONRY") (62 . 7) (370 . 13) (100 . "AcDbLine") (10 9754.901040724
1380.0904977376 0.0) (11 9743.5888235294 1380.0904977376 0.0))
((0 . "LINE") (100 . "AcDbEntity") (8 . "MASONRY") (62 . 7) (370 . 13) (100 . "AcDbLine") (10 9860.4835746606
2110.4099773756 0.0) (11 9747.3614027149 2110.4099773756 0.0))
((0 . "LINE") (100 . "AcDbEntity") (8 . "MASONRY") (62 . 7) (370 . 13) (100 . "AcDbLine") (10 9754.901040724
3559.5779072398 0.0) (11 9754.901040724 3552.036199095 0.0))
((0 . "LINE") (100 . "AcDbEntity") (8 . "MASONRY") (62 . 7) (370 . 13) (100 . "AcDbLine") (10 9753.0161312217
1934.3891402715 0.0) (11 9753.0161312217 1987.1797171946 0.0))
((0 . "LINE") (100 . "AcDbEntity") (8 . "MASONRY") (62 . 7) (370 . 13) (100 . "AcDbLine") (10 9754.901040724
4098.7938235294 0.0) (11 9754.901040724 4068.6269909502 0.0))
((0 . "LINE") (100 . "AcDbEntity") (8 . "MASONRY") (62 . 7) (370 . 13) (100 . "AcDbLine") (10 9754.901040724
4098.7938235294 0.0) (11 9860.6672285068 4098.7938235294 0.0))
((0 . "LINE") (100 . "AcDbEntity") (8 . "MASONRY") (62 . 7) (370 . 13) (100 . "AcDbLine") (10 9754.901040724
4068.6269909502 0.0) (11 9762.443438914 4068.6269909502 0.0))
((0 . "LINE") (100 . "AcDbEntity") (8 . "MASONRY") (62 . 7) (370 . 13) (100 . "AcDbLine") (10 9754.901040724
3559.5779072398 0.0) (11 9754.901040724 3597.2850678733 0.0))
((0 . "LINE") (100 . "AcDbEntity") (8 . "MASONRY") (62 . 7) (370 . 13) (100 . "AcDbLine") (10 9988.6877828054
3597.2850678733 0.0) (11 9754.901040724 3597.2850678733 0.0))
((0 . "LINE") (100 . "AcDbEntity") (8 . "MASONRY") (62 . 7) (370 . 13) (100 . "AcDbLine") (10 9754.901040724
3559.5779072398 0.0) (11 9852.9411764706 3559.5779072398 0.0))
((0 . "LINE") (100 . "AcDbEntity") (8 . "MASONRY") (62 . 7) (370 . 13) (100 . "AcDbLine") (10 9937.7054751131
1987.1797171946 0.0) (11 9753.0161312217 1987.1797171946 0.0))
((0 . "LINE") (100 . "AcDbEntity") (8 . "MASONRY") (62 . 7) (370 . 13) (100 . "AcDbLine") (10 9877.450520362
6206.6363800905 0.0) (11 9762.443438914 6206.6363800905 0.0))
((0 . "LINE") (100 . "AcDbEntity") (8 . "MASONRY") (62 . 7) (370 . 13) (100 . "AcDbLine") (10 9884.9155882353
5248.8687782805 0.0) (11 9884.9155882353 5316.8967420814 0.0))
((0 . "LINE") (100 . "AcDbEntity") (8 . "MASONRY") (62 . 7) (370 . 13) (100 . "AcDbLine") (10 9884.9155882353
5316.8967420814 0.0) (11 9807.6985180995 5316.8967420814 0.0))
((0 . "LINE") (100 . "AcDbEntity") (8 . "MASONRY") (62 . 7) (370 . 13) (100 . "AcDbLine") (10 9807.6985180995
5316.8967420814 0.0) (11 9766.2132579186 5316.8967420814 0.0))
((0 . "LINE") (100 . "AcDbEntity") (8 . "MASONRY") (62 . 7) (370 . 13) (100 . "AcDbLine") (10 9766.2132579186
2894.0426923077 0.0) (11 9875.5656108597 2894.0426923077 0.0))
((0 . "LINE") (100 . "AcDbEntity") (8 . "MASONRY") (62 . 7) (370 . 13) (100 . "AcDbLine") (10 9781.2966742081
260.1809954751 0.0) (11 9766.2132579186 260.1809954751 0.0))
((0 . "LINE") (100 . "AcDbEntity") (8 . "MASONRY") (62 . 7) (370 . 13) (100 . "AcDbLine") (10 9782.6547737557
5791.8552036199 0.0) (11 9782.6547737557 5765.4599095023 0.0))
((0 . "LINE") (100 . "AcDbEntity") (8 . "MASONRY") (62 . 7) (370 . 13) (100 . "AcDbLine") (10 9782.6547737557
5765.4599095023 0.0) (11 9782.6547737557 5750.3771945701 0.0))
((0 . "LINE") (100 . "AcDbEntity") (8 . "MASONRY") (62 . 7) (370 . 13) (100 . "AcDbLine") (10 9769.9858371041
1608.2211312217 0.0) (11 9826.5469230769 1608.2211312217 0.0))
((0 . "LINE") (100 . "AcDbEntity") (8 . "MASONRY") (62 . 7) (370 . 13) (100 . "AcDbLine") (10 9773.7556561086
6255.6561085973 0.0) (11 9773.7556561086 6297.2887782805 0.0))
((0 . "LINE") (100 . "AcDbEntity") (8 . "MASONRY") (62 . 7) (370 . 13) (100 . "AcDbLine") (10 9966.0633484163
6297.2887782805 0.0) (11 9773.7556561086 6297.2887782805 0.0))
((0 . "LINE") (100 . "AcDbEntity") (8 . "MASONRY") (62 . 7) (370 . 13) (100 . "AcDbLine") (10 9773.7556561086
6255.6561085973 0.0) (11 9943.4389140272 6255.6561085973 0.0))
((0 . "LINE") (100 . "AcDbEntity") (8 . "MASONRY") (62 . 7) (370 . 13) (100 . "AcDbLine") (10 9777.5254751131
3695.3238235294 0.0) (11 9785.0678733032 3695.3238235294 0.0))
((0 . "LINE") (100 . "AcDbEntity") (8 . "MASONRY") (62 . 7) (370 . 13) (100 . "AcDbLine") (10 9785.0678733032
1738.3116289593 0.0) (11 9785.0678733032 1800.4508031674 0.0))
((0 . "LINE") (100 . "AcDbEntity") (8 . "MASONRY") (62 . 7) (370 . 13) (100 . "AcDbLine") (10 9807.6923076923
1234.9165837104 0.0) (11 9777.5254751131 1234.9165837104 0.0))
((0 . "LINE") (100 . "AcDbEntity") (8 . "MASONRY") (62 . 7) (370 . 13) (100 . "AcDbLine") (10 9781.2966742081
260.1809954751 0.0) (11 9939.6690950226 260.1809954751 0.0))
((0 . "LINE") (100 . "AcDbEntity") (8 . "MASONRY") (62 . 7) (370 . 13) (100 . "AcDbLine") (10 9781.2966742081
260.1809954751 0.0) (11 9781.2966742081 354.4485520362 0.0))
((0 . "LINE") (100 . "AcDbEntity") (8 . "MASONRY") (62 . 7) (370 . 13) (100 . "AcDbLine") (10 9781.2980542986
6104.8264253394 0.0) (11 9796.3800904977 6104.8264253394 0.0))
((0 . "LINE") (100 . "AcDbEntity") (8 . "MASONRY") (62 . 7) (370 . 13) (100 . "AcDbLine") (10 9782.6547737557
5791.8552036199 0.0) (11 9782.6547737557 5833.3332126697 0.0))
((0 . "LINE") (100 . "AcDbEntity") (8 . "MASONRY") (62 . 7) (370 . 13) (100 . "AcDbLine") (10 9864.2533936652
5109.3509728507 0.0) (11 9796.386300905 5109.3509728507 0.0))
((0 . "LINE") (100 . "AcDbEntity") (8 . "MASONRY") (62 . 7) (370 . 13) (100 . "AcDbLine") (10 9796.386300905
5109.3509728507 0.0) (11 9785.0678733032 5109.3509728507 0.0))
((0 . "LINE") (100 . "AcDbEntity") (8 . "MASONRY") (62 . 7) (370 . 13) (100 . "AcDbLine") (10 9785.0678733032
5135.5919457014 0.0) (11 9785.0678733032 5109.3509728507 0.0))
((0 . "LINE") (100 . "AcDbEntity") (8 . "MASONRY") (62 . 7) (370 . 13) (100 . "AcDbLine") (10 9913.272081448
1340.4977375566 0.0) (11 9781.2980542986 1340.4977375566 0.0))
((0 . "LINE") (100 . "AcDbEntity") (8 . "MASONRY") (62 . 7) (370 . 13) (100 . "AcDbLine") (10 9782.6547737557
5833.3332126697 0.0) (11 9879.3354298643 5833.3332126697 0.0))
((0 . "LINE") (100 . "AcDbEntity") (8 . "MASONRY") (62 . 7) (370 . 13) (100 . "AcDbLine") (10 9785.0678733032
3695.3238235294 0.0) (11 9785.0678733032 3706.636040724 0.0))
((0 . "LINE") (100 . "AcDbEntity") (8 . "MASONRY") (62 . 7) (370 . 13) (100 . "AcDbLine") (10 9841.628959276
3695.3238235294 0.0) (11 9785.0678733032 3695.3238235294 0.0))
((0 . "LINE") (100 . "AcDbEntity") (8 . "MASONRY") (62 . 7) (370 . 13) (100 . "AcDbLine") (10 9786.9527828054
2948.718178733 0.0) (11 9786.9527828054 3035.4447171946 0.0))
((0 . "LINE") (100 . "AcDbEntity") (8 . "MASONRY") (62 . 7) (370 . 13) (100 . "AcDbLine") (10 9815.2347058824
3035.4447171946 0.0) (11 9786.9527828054 3035.4447171946 0.0))
((0 . "LINE") (100 . "AcDbEntity") (8 . "MASONRY") (62 . 7) (370 . 13) (100 . "AcDbLine") (10 9785.0678733032
1855.2036199095 0.0) (11 9785.0678733032 1800.4508031674 0.0))
((0 . "LINE") (100 . "AcDbEntity") (8 . "MASONRY") (62 . 7) (370 . 13) (100 . "AcDbLine") (10 9785.0678733032
1800.4508031674 0.0) (11 9873.679321267 1800.4508031674 0.0))
((0 . "LINE") (100 . "AcDbEntity") (8 . "MASONRY") (62 . 7) (370 . 13) (100 . "AcDbLine") (10 9873.679321267
1800.4508031674 0.0) (11 9873.679321267 1776.0180995475 0.0))
((0 . "LINE") (100 . "AcDbEntity") (8 . "MASONRY") (62 . 7) (370 . 13) (100 . "AcDbLine") (10 9852.9411764706
354.4485520362 0.0) (11 9781.2966742081 354.4485520362 0.0))
((0 . "LINE") (100 . "AcDbEntity") (8 . "MASONRY") (62 . 7) (370 . 13) (100 . "AcDbLine") (10 9785.0678733032
5135.5919457014 0.0) (11 9969.8331674208 5135.5919457014 0.0))
((0 . "LINE") (100 . "AcDbEntity") (8 . "MASONRY") (62 . 7) (370 . 13) (100 . "AcDbLine") (10 9969.8331674208
5135.5919457014 0.0) (11 10000 5135.5919457014 0.0))
((0 . "LINE") (100 . "AcDbEntity") (8 . "MASONRY") (62 . 7) (370 . 13) (100 . "AcDbLine") (10 10000 5135.5919457014 0.0)
(11 10354.4485520362 5135.5919457014 0.0))
((0 . "LINE") (100 . "AcDbEntity") (8 . "MASONRY") (62 . 7) (370 . 13) (100 . "AcDbLine") (10 9898.1900452489
5439.2908710407 0.0) (11 9788.8363122172 5439.2908710407 0.0))
((0 . "LINE") (100 . "AcDbEntity") (8 . "MASONRY") (62 . 7) (370 . 13) (100 . "AcDbLine") (10 9792.6102714932
2326.5462330317 0.0) (11 9792.6102714932 2345.3994683258 0.0))
((0 . "LINE") (100 . "AcDbEntity") (8 . "MASONRY") (62 . 7) (370 . 13) (100 . "AcDbLine") (10 9867.3693665158
537.3303167421 0.0) (11 9792.6102714932 537.3303167421 0.0))
((0 . "LINE") (100 . "AcDbEntity") (8 . "MASONRY") (62 . 7) (370 . 13) (100 . "AcDbLine") (10 9803.9224886878 4475.8675
0.0) (11 9796.3800904977 4475.8675 0.0))
((0 . "LINE") (100 . "AcDbEntity") (8 . "MASONRY") (62 . 7) (370 . 13) (100 . "AcDbLine") (10 9798.265 4411.7647058824
0.0) (11 9815.2347058824 4411.7647058824 0.0))
((0 . "LINE") (100 . "AcDbEntity") (8 . "MASONRY") (62 . 7) (370 . 13) (100 . "AcDbLine") (10 9798.265 4411.7647058824
0.0) (11 9798.265 4434.3891402715 0.0))
((0 . "LINE") (100 . "AcDbEntity") (8 . "MASONRY") (62 . 7) (370 . 13) (100 . "AcDbLine") (10 9796.3800904977
4068.6269909502 0.0) (11 9811.4621266968 4068.6269909502 0.0))
((0 . "LINE") (100 . "AcDbEntity") (8 . "MASONRY") (62 . 7) (370 . 13) (100 . "AcDbLine") (10 9796.3800904977
2269.9851470588 0.0) (11 9796.3800904977 2303.9217986425 0.0))
((0 . "LINE") (100 . "AcDbEntity") (8 . "MASONRY") (62 . 7) (370 . 13) (100 . "AcDbLine") (10 9811.4621266968
2269.9851470588 0.0) (11 9796.3800904977 2269.9851470588 0.0))
((0 . "LINE") (100 . "AcDbEntity") (8 . "MASONRY") (62 . 7) (370 . 13) (100 . "AcDbLine") (10 9888.7627375566
991.7052941176 0.0) (11 9800.1512895928 991.7052941176 0.0))
((0 . "LINE") (100 . "AcDbEntity") (8 . "MASONRY") (62 . 7) (370 . 13) (100 . "AcDbLine") (10 9800.1512895928
946.4564253394 0.0) (11 9800.1512895928 991.7052941176 0.0))
((0 . "LINE") (100 . "AcDbEntity") (8 . "MASONRY") (62 . 7) (370 . 13) (100 . "AcDbLine") (10 9803.9211085973
4973.6043665158 0.0) (11 9803.9211085973 4992.4589819005 0.0))
((0 . "LINE") (100 . "AcDbEntity") (8 . "MASONRY") (62 . 7) (370 . 13) (100 . "AcDbLine") (10 9798.2615497738
4892.5339366516 0.0) (11 9911.3871719457 4892.5339366516 0.0))
((0 . "LINE") (100 . "AcDbEntity") (8 . "MASONRY") (62 . 7) (370 . 13) (100 . "AcDbLine") (10 9800.1499095023
3394.2672285068 0.0) (11 9800.1499095023 3335.2184728507 0.0))
((0 . "LINE") (100 . "AcDbEntity") (8 . "MASONRY") (62 . 7) (370 . 13) (100 . "AcDbLine") (10 9800.1499095023
3335.2184728507 0.0) (11 9819.0045248869 3335.2184728507 0.0))
((0 . "LINE") (100 . "AcDbEntity") (8 . "MASONRY") (62 . 7) (370 . 13) (100 . "AcDbLine") (10 9800.1499095023
3394.2672285068 0.0) (11 9800.1499095023 3414.4046832579 0.0))
((0 . "LINE") (100 . "AcDbEntity") (8 . "MASONRY") (62 . 7) (370 . 13) (100 . "AcDbLine") (10 9800.1499095023
3394.2672285068 0.0) (11 9822.7722737557 3394.2672285068 0.0))
((0 . "LINE") (100 . "AcDbEntity") (8 . "MASONRY") (62 . 7) (370 . 13) (100 . "AcDbLine") (10 9822.7722737557
3394.2672285068 0.0) (11 9822.7722737557 3414.4046832579 0.0))
((0 . "LINE") (100 . "AcDbEntity") (8 . "MASONRY") (62 . 7) (370 . 13) (100 . "AcDbLine") (10 9890.6476470588
1930.6186312217 0.0) (11 9800.1499095023 1930.6186312217 0.0))
((0 . "LINE") (100 . "AcDbEntity") (8 . "MASONRY") (62 . 7) (370 . 13) (100 . "AcDbLine") (10 9800.1499095023
1040.5755316742 0.0) (11 9822.7743438914 1040.5755316742 0.0))
((0 . "LINE") (100 . "AcDbEntity") (8 . "MASONRY") (62 . 7) (370 . 13) (100 . "AcDbLine") (10 9822.7743438914
1040.5755316742 0.0) (11 9884.9887782805 1040.5755316742 0.0))
((0 . "LINE") (100 . "AcDbEntity") (8 . "MASONRY") (62 . 7) (370 . 13) (100 . "AcDbLine") (10 9884.9887782805
1040.5755316742 0.0) (11 9884.9887782805 1093.5152488688 0.0))
((0 . "LINE") (100 . "AcDbEntity") (8 . "MASONRY") (62 . 7) (370 . 13) (100 . "AcDbLine") (10 9800.1499095023
848.4162895928 0.0) (11 9815.2347058824 848.4162895928 0.0))
((0 . "LINE") (100 . "AcDbEntity") (8 . "MASONRY") (62 . 7) (370 . 13) (100 . "AcDbLine") (10 9800.1499095023
3414.4046832579 0.0) (11 9822.7722737557 3414.4046832579 0.0))
((0 . "LINE") (100 . "AcDbEntity") (8 . "MASONRY") (62 . 7) (370 . 13) (100 . "AcDbLine") (10 9856.7109954751
801.2825113122 0.0) (11 9803.9224886878 801.2825113122 0.0))
((0 . "LINE") (100 . "AcDbEntity") (8 . "MASONRY") (62 . 7) (370 . 13) (100 . "AcDbLine") (10 9807.6923076923
6108.5972850679 0.0) (11 9826.5469230769 6108.5972850679 0.0))
((0 . "LINE") (100 . "AcDbEntity") (8 . "MASONRY") (62 . 7) (370 . 13) (100 . "AcDbLine") (10 9809.5772171946
188.5378733032 0.0) (11 9809.5772171946 177.2256561086 0.0))
((0 . "LINE") (100 . "AcDbEntity") (8 . "MASONRY") (62 . 7) (370 . 13) (100 . "AcDbLine") (10 9809.5772171946
177.2256561086 0.0) (11 9952.8689819005 177.2256561086 0.0))
((0 . "LINE") (100 . "AcDbEntity") (8 . "MASONRY") (62 . 7) (370 . 13) (100 . "AcDbLine") (10 9811.4621266968
2269.9851470588 0.0) (11 9811.4621266968 2237.9340950226 0.0))
((0 . "LINE") (100 . "AcDbEntity") (8 . "MASONRY") (62 . 7) (370 . 13) (100 . "AcDbLine") (10 9901.9598642534
2269.9851470588 0.0) (11 9811.4621266968 2269.9851470588 0.0))
((0 . "LINE") (100 . "AcDbEntity") (8 . "MASONRY") (62 . 7) (370 . 13) (100 . "AcDbLine") (10 9811.4621266968
2237.9340950226 0.0) (11 9826.5469230769 2237.9340950226 0.0))
((0 . "LINE") (100 . "AcDbEntity") (8 . "MASONRY") (62 . 7) (370 . 13) (100 . "AcDbLine") (10 9822.7743438914
1855.2036199095 0.0) (11 9834.086561086 1855.2036199095 0.0))
((0 . "LINE") (100 . "AcDbEntity") (8 . "MASONRY") (62 . 7) (370 . 13) (100 . "AcDbLine") (10 9830.3167420814
1525.2644117647 0.0) (11 9822.7743438914 1525.2644117647 0.0))
((0 . "LINE") (100 . "AcDbEntity") (8 . "MASONRY") (62 . 7) (370 . 13) (100 . "AcDbLine") (10 9822.7743438914
1481.9004524887 0.0) (11 9822.7743438914 1474.3580542986 0.0))
((0 . "LINE") (100 . "AcDbEntity") (8 . "MASONRY") (62 . 7) (370 . 13) (100 . "AcDbLine") (10 9822.7722737557
3414.4046832579 0.0) (11 9905.7324434389 3414.4046832579 0.0))
((0 . "LINE") (100 . "AcDbEntity") (8 . "MASONRY") (62 . 7) (370 . 13) (100 . "AcDbLine") (10 9830.3167420814
3050.5274434389 0.0) (11 9852.9411764706 3050.5274434389 0.0))
((0 . "LINE") (100 . "AcDbEntity") (8 . "MASONRY") (62 . 7) (370 . 13) (100 . "AcDbLine") (10 9834.086561086
3325.7918552036 0.0) (11 9992.45760181 3325.7918552036 0.0))
((0 . "LINE") (100 . "AcDbEntity") (8 . "MASONRY") (62 . 7) (370 . 13) (100 . "AcDbLine") (10 9905.7324434389
6114.2533936652 0.0) (11 9837.8591402715 6114.2533936652 0.0))
((0 . "LINE") (100 . "AcDbEntity") (8 . "MASONRY") (62 . 7) (370 . 13) (100 . "AcDbLine") (10 9837.8591402715
4408.1485067873 0.0) (11 9868.0232126697 4408.1485067873 0.0))
((0 . "LINE") (100 . "AcDbEntity") (8 . "MASONRY") (62 . 7) (370 . 13) (100 . "AcDbLine") (10 9841.628959276
2944.946979638 0.0) (11 9920.814479638 2944.946979638 0.0))
((0 . "LINE") (100 . "AcDbEntity") (8 . "MASONRY") (62 . 7) (370 . 13) (100 . "AcDbLine") (10 9841.628959276
2232.2772963801 0.0) (11 9898.1900452489 2232.2772963801 0.0))
((0 . "LINE") (100 . "AcDbEntity") (8 . "MASONRY") (62 . 7) (370 . 13) (100 . "AcDbLine") (10 9841.628959276
1238.6877828054 0.0) (11 9851.0562669683 1238.6877828054 0.0))
((0 . "LINE") (100 . "AcDbEntity") (8 . "MASONRY") (62 . 7) (370 . 13) (100 . "AcDbLine") (10 9860.4835746606
4268.4763914027 0.0) (11 9849.1713574661 4268.4763914027 0.0))
((0 . "LINE") (100 . "AcDbEntity") (8 . "MASONRY") (62 . 7) (370 . 13) (100 . "AcDbLine") (10 9851.0562669683
1251.8862895928 0.0) (11 9851.0562669683 1238.6877828054 0.0))
((0 . "LINE") (100 . "AcDbEntity") (8 . "MASONRY") (62 . 7) (370 . 13) (100 . "AcDbLine") (10 9901.9598642534
1238.6877828054 0.0) (11 9851.0562669683 1238.6877828054 0.0))
((0 . "LINE") (100 . "AcDbEntity") (8 . "MASONRY") (62 . 7) (370 . 13) (100 . "AcDbLine") (10 10237.556561086
477.0795022624 0.0) (11 9852.9453167421 477.0795022624 0.0))
((0 . "LINE") (100 . "AcDbEntity") (8 . "MASONRY") (62 . 7) (370 . 13) (100 . "AcDbLine") (10 9852.9453167421
477.0795022624 0.0) (11 9852.9453167421 490.195158371 0.0))
((0 . "LINE") (100 . "AcDbEntity") (8 . "MASONRY") (62 . 7) (370 . 13) (100 . "AcDbLine") (10 9879.3354298643
5908.7482352941 0.0) (11 9852.9411764706 5908.7482352941 0.0))
((0 . "LINE") (100 . "AcDbEntity") (8 . "MASONRY") (62 . 7) (370 . 13) (100 . "AcDbLine") (10 9858.5972850679
4660.6334841629 0.0) (11 9858.5972850679 4690.7989366516 0.0))
((0 . "LINE") (100 . "AcDbEntity") (8 . "MASONRY") (62 . 7) (370 . 13) (100 . "AcDbLine") (10 9911.3871719457
848.4162895928 0.0) (11 9852.9411764706 848.4162895928 0.0))
((0 . "LINE") (100 . "AcDbEntity") (8 . "MASONRY") (62 . 7) (370 . 13) (100 . "AcDbLine") (10 9852.9411764706
384.6153846154 0.0) (11 9852.9411764706 354.4485520362 0.0))
((0 . "LINE") (100 . "AcDbEntity") (8 . "MASONRY") (62 . 7) (370 . 13) (100 . "AcDbLine") (10 9852.9411764706
354.4485520362 0.0) (11 10098.0401357466 354.4485520362 0.0))
((0 . "LINE") (100 . "AcDbEntity") (8 . "MASONRY") (62 . 7) (370 . 13) (100 . "AcDbLine") (10 9947.2087330317
3288.0846945701 0.0) (11 9856.7109954751 3288.0846945701 0.0))
((0 . "LINE") (100 . "AcDbEntity") (8 . "MASONRY") (62 . 7) (370 . 13) (100 . "AcDbLine") (10 9862.3671040724
3190.0452488688 0.0) (11 9928.3568778281 3190.0452488688 0.0))
((0 . "LINE") (100 . "AcDbEntity") (8 . "MASONRY") (62 . 7) (370 . 13) (100 . "AcDbLine") (10 9862.3671040724
3148.5668891403 0.0) (11 9862.3671040724 3190.0452488688 0.0))
((0 . "LINE") (100 . "AcDbEntity") (8 . "MASONRY") (62 . 7) (370 . 13) (100 . "AcDbLine") (10 9932.1266968326
2175.7169004525 0.0) (11 9856.7109954751 2175.7169004525 0.0))
((0 . "LINE") (100 . "AcDbEntity") (8 . "MASONRY") (62 . 7) (370 . 13) (100 . "AcDbLine") (10 9856.7109954751
1738.913699095 0.0) (11 9877.3731900452 1738.913699095 0.0))
((0 . "LINE") (100 . "AcDbEntity") (8 . "MASONRY") (62 . 7) (370 . 13) (100 . "AcDbLine") (10 9877.3731900452
1738.913699095 0.0) (11 9877.3731900452 1753.3936651584 0.0))
((0 . "LINE") (100 . "AcDbEntity") (8 . "MASONRY") (62 . 7) (370 . 13) (100 . "AcDbLine") (10 9860.6672285068
4098.7938235294 0.0) (11 9860.6672285068 4066.819061086 0.0))
((0 . "LINE") (100 . "AcDbEntity") (8 . "MASONRY") (62 . 7) (370 . 13) (100 . "AcDbLine") (10 9860.6672285068
4066.819061086 0.0) (11 9973.6043665158 4066.819061086 0.0))
((0 . "LINE") (100 . "AcDbEntity") (8 . "MASONRY") (62 . 7) (370 . 13) (100 . "AcDbLine") (10 9973.6043665158
4066.819061086 0.0) (11 9973.6043665158 4079.9392081448 0.0))
((0 . "LINE") (100 . "AcDbEntity") (8 . "MASONRY") (62 . 7) (370 . 13) (100 . "AcDbLine") (10 9860.6672285068
4098.7938235294 0.0) (11 9977.4494457014 4098.7938235294 0.0))
((0 . "LINE") (100 . "AcDbEntity") (8 . "MASONRY") (62 . 7) (370 . 13) (100 . "AcDbLine") (10 9977.4494457014
4098.7938235294 0.0) (11 9977.4494457014 4137.7099547511 0.0))
((0 . "LINE") (100 . "AcDbEntity") (8 . "MASONRY") (62 . 7) (370 . 13) (100 . "AcDbLine") (10 9977.4494457014
4137.7099547511 0.0) (11 10000 4137.7099547511 0.0))
((0 . "LINE") (100 . "AcDbEntity") (8 . "MASONRY") (62 . 7) (370 . 13) (100 . "AcDbLine") (10 9860.4835746606
3753.7705090498 0.0) (11 9890.6476470588 3753.7705090498 0.0))
((0 . "LINE") (100 . "AcDbEntity") (8 . "MASONRY") (62 . 7) (370 . 13) (100 . "AcDbLine") (10 9860.4835746606
2110.4099773756 0.0) (11 9860.4835746606 2126.6968325792 0.0))
((0 . "LINE") (100 . "AcDbEntity") (8 . "MASONRY") (62 . 7) (370 . 13) (100 . "AcDbLine") (10 9860.4835746606
2110.4099773756 0.0) (11 9981.3007352941 2110.4099773756 0.0))
((0 . "LINE") (100 . "AcDbEntity") (8 . "MASONRY") (62 . 7) (370 . 13) (100 . "AcDbLine") (10 9981.3007352941
2110.4099773756 0.0) (11 9981.3007352941 2055.053020362 0.0))
((0 . "LINE") (100 . "AcDbEntity") (8 . "MASONRY") (62 . 7) (370 . 13) (100 . "AcDbLine") (10 9981.3007352941
2055.053020362 0.0) (11 9981.3007352941 2045.7037330317 0.0))
((0 . "LINE") (100 . "AcDbEntity") (8 . "MASONRY") (62 . 7) (370 . 13) (100 . "AcDbLine") (10 9981.3007352941
2045.7037330317 0.0) (11 10331.8241176471 2045.7037330317 0.0))
((0 . "LINE") (100 . "AcDbEntity") (8 . "MASONRY") (62 . 7) (370 . 13) (100 . "AcDbLine") (10 9860.4835746606
1858.9748190045 0.0) (11 9881.221719457 1858.9748190045 0.0))
((0 . "LINE") (100 . "AcDbEntity") (8 . "MASONRY") (62 . 7) (370 . 13) (100 . "AcDbLine") (10 9866.1383031674
4340.0435633484 0.0) (11 9866.1383031674 4377.8280542986 0.0))
((0 . "LINE") (100 . "AcDbEntity") (8 . "MASONRY") (62 . 7) (370 . 13) (100 . "AcDbLine") (10 9866.1383031674
4193.0613800905 0.0) (11 9866.1383031674 4136.5002941176 0.0))
((0 . "LINE") (100 . "AcDbEntity") (8 . "MASONRY") (62 . 7) (370 . 13) (100 . "AcDbLine") (10 9890.6476470588
2635.7466063348 0.0) (11 9864.2533936652 2635.7466063348 0.0))
((0 . "LINE") (100 . "AcDbEntity") (8 . "MASONRY") (62 . 7) (370 . 13) (100 . "AcDbLine") (10 9981.1453846154
1523.3795022624 0.0) (11 9864.2533936652 1523.3795022624 0.0))
((0 . "LINE") (100 . "AcDbEntity") (8 . "MASONRY") (62 . 7) (370 . 13) (100 . "AcDbLine") (10 9867.3693665158
537.3303167421 0.0) (11 9867.3693665158 572.9682239819 0.0))
((0 . "LINE") (100 . "AcDbEntity") (8 . "MASONRY") (62 . 7) (370 . 13) (100 . "AcDbLine") (10 9867.3693665158
572.9682239819 0.0) (11 9890.6476470588 572.9682239819 0.0))
((0 . "LINE") (100 . "AcDbEntity") (8 . "MASONRY") (62 . 7) (370 . 13) (100 . "AcDbLine") (10 9867.3693665158
537.3303167421 0.0) (11 9969.8331674208 537.3303167421 0.0))
((0 . "LINE") (100 . "AcDbEntity") (8 . "MASONRY") (62 . 7) (370 . 13) (100 . "AcDbLine") (10 9868.0232126697
4408.1485067873 0.0) (11 10109.3482126697 4408.1485067873 0.0))
((0 . "LINE") (100 . "AcDbEntity") (8 . "MASONRY") (62 . 7) (370 . 13) (100 . "AcDbLine") (10 10109.3482126697
4408.1485067873 0.0) (11 10109.3482126697 4445.7013574661 0.0))
((0 . "LINE") (100 . "AcDbEntity") (8 . "MASONRY") (62 . 7) (370 . 13) (100 . "AcDbLine") (10 9868.0232126697
4400.4524886878 0.0) (11 9868.0232126697 4408.1485067873 0.0))
((0 . "LINE") (100 . "AcDbEntity") (8 . "MASONRY") (62 . 7) (370 . 13) (100 . "AcDbLine") (10 9866.1383031674
4340.0435633484 0.0) (11 10060.3309049774 4340.0435633484 0.0))
((0 . "LINE") (100 . "AcDbEntity") (8 . "MASONRY") (62 . 7) (370 . 13) (100 . "AcDbLine") (10 9866.1383031674
4193.0613800905 0.0) (11 9988.6877828054 4193.0613800905 0.0))
((0 . "LINE") (100 . "AcDbEntity") (8 . "MASONRY") (62 . 7) (370 . 13) (100 . "AcDbLine") (10 9988.6877828054
4193.0613800905 0.0) (11 9988.6877828054 4211.9159954751 0.0))
((0 . "LINE") (100 . "AcDbEntity") (8 . "MASONRY") (62 . 7) (370 . 13) (100 . "AcDbLine") (10 9868.0232126697
2767.7227036199 0.0) (11 9920.814479638 2767.7227036199 0.0))
((0 . "LINE") (100 . "AcDbEntity") (8 . "MASONRY") (62 . 7) (370 . 13) (100 . "AcDbLine") (10 9871.7957918552
3059.9547511312 0.0) (11 10045.2488687783 3059.9547511312 0.0))
((0 . "LINE") (100 . "AcDbEntity") (8 . "MASONRY") (62 . 7) (370 . 13) (100 . "AcDbLine") (10 9879.3354298643
2405.7317533937 0.0) (11 9871.7957918552 2405.7317533937 0.0))
((0 . "LINE") (100 . "AcDbEntity") (8 . "MASONRY") (62 . 7) (370 . 13) (100 . "AcDbLine") (10 9877.450520362
6206.6363800905 0.0) (11 9966.0633484163 6206.6363800905 0.0))
((0 . "LINE") (100 . "AcDbEntity") (8 . "MASONRY") (62 . 7) (370 . 13) (100 . "AcDbLine") (10 9879.3354298643
5908.7482352941 0.0) (11 9879.3354298643 5878.582081448 0.0))
((0 . "LINE") (100 . "AcDbEntity") (8 . "MASONRY") (62 . 7) (370 . 13) (100 . "AcDbLine") (10 9879.3354298643
5908.7482352941 0.0) (11 9879.3354298643 5923.8309502262 0.0))
((0 . "LINE") (100 . "AcDbEntity") (8 . "MASONRY") (62 . 7) (370 . 13) (100 . "AcDbLine") (10 9924.5842986425
3557.6923076923 0.0) (11 9875.5656108597 3557.6923076923 0.0))
((0 . "LINE") (100 . "AcDbEntity") (8 . "MASONRY") (62 . 7) (370 . 13) (100 . "AcDbLine") (10 9879.3354298643
5833.3332126697 0.0) (11 9879.3354298643 5855.9576470588 0.0))
((0 . "LINE") (100 . "AcDbEntity") (8 . "MASONRY") (62 . 7) (370 . 13) (100 . "AcDbLine") (10 10105.5797737557
5833.3332126697 0.0) (11 9879.3354298643 5833.3332126697 0.0))
((0 . "LINE") (100 . "AcDbEntity") (8 . "MASONRY") (62 . 7) (370 . 13) (100 . "AcDbLine") (10 9884.9915384615
3714.178438914 0.0) (11 9884.9915384615 3691.5540045249 0.0))
((0 . "LINE") (100 . "AcDbEntity") (8 . "MASONRY") (62 . 7) (370 . 13) (100 . "AcDbLine") (10 9879.3354298643
2488.6877828054 0.0) (11 9879.3354298643 2458.5216402715 0.0))
((0 . "LINE") (100 . "AcDbEntity") (8 . "MASONRY") (62 . 7) (370 . 13) (100 . "AcDbLine") (10 9879.3354298643
2405.7317533937 0.0) (11 9879.3354298643 2458.5216402715 0.0))
((0 . "LINE") (100 . "AcDbEntity") (8 . "MASONRY") (62 . 7) (370 . 13) (100 . "AcDbLine") (10 9881.221719457
1828.8086764706 0.0) (11 9881.221719457 1858.9748190045 0.0))
((0 . "LINE") (100 . "AcDbEntity") (8 . "MASONRY") (62 . 7) (370 . 13) (100 . "AcDbLine") (10 9941.5540045249
1858.9748190045 0.0) (11 9881.221719457 1858.9748190045 0.0))
((0 . "LINE") (100 . "AcDbEntity") (8 . "MASONRY") (62 . 7) (370 . 13) (100 . "AcDbLine") (10 9901.9598642534
1259.4259276018 0.0) (11 9879.3354298643 1259.4259276018 0.0))
((0 . "LINE") (100 . "AcDbEntity") (8 . "MASONRY") (62 . 7) (370 . 13) (100 . "AcDbLine") (10 9884.9155882353
5248.8687782805 0.0) (11 9969.8331674208 5248.8687782805 0.0))
((0 . "LINE") (100 . "AcDbEntity") (8 . "MASONRY") (62 . 7) (370 . 13) (100 . "AcDbLine") (10 9888.7627375566
3974.3594343891 0.0) (11 9888.7627375566 3989.4414705882 0.0))
((0 . "LINE") (100 . "AcDbEntity") (8 . "MASONRY") (62 . 7) (370 . 13) (100 . "AcDbLine") (10 9977.3755656109
4021.6416628959 0.0) (11 9977.3755656109 3989.4414705882 0.0))
((0 . "LINE") (100 . "AcDbEntity") (8 . "MASONRY") (62 . 7) (370 . 13) (100 . "AcDbLine") (10 9977.3755656109
3989.4414705882 0.0) (11 9888.7627375566 3989.4414705882 0.0))
((0 . "LINE") (100 . "AcDbEntity") (8 . "MASONRY") (62 . 7) (370 . 13) (100 . "AcDbLine") (10 9888.7627375566
3863.1221719457 0.0) (11 9888.7627375566 3804.6761764706 0.0))
((0 . "LINE") (100 . "AcDbEntity") (8 . "MASONRY") (62 . 7) (370 . 13) (100 . "AcDbLine") (10 9879.3354298643
2405.7317533937 0.0) (11 9898.1900452489 2405.7317533937 0.0))
((0 . "LINE") (100 . "AcDbEntity") (8 . "MASONRY") (62 . 7) (370 . 13) (100 . "AcDbLine") (10 9920.814479638
1163.2734615385 0.0) (11 9886.8778280543 1163.2734615385 0.0))
((0 . "LINE") (100 . "AcDbEntity") (8 . "MASONRY") (62 . 7) (370 . 13) (100 . "AcDbLine") (10 9888.7627375566
1010.5571493213 0.0) (11 9888.7627375566 991.7052941176 0.0))
((0 . "LINE") (100 . "AcDbEntity") (8 . "MASONRY") (62 . 7) (370 . 13) (100 . "AcDbLine") (10 9890.6476470588
4624.8112330317 0.0) (11 9992.45760181 4624.8112330317 0.0))
((0 . "LINE") (100 . "AcDbEntity") (8 . "MASONRY") (62 . 7) (370 . 13) (100 . "AcDbLine") (10 10143.2876244344
3863.1221719457 0.0) (11 10116.8919909502 3863.1221719457 0.0))
((0 . "LINE") (100 . "AcDbEntity") (8 . "MASONRY") (62 . 7) (370 . 13) (100 . "AcDbLine") (10 10116.8919909502
3863.1221719457 0.0) (11 9888.7627375566 3863.1221719457 0.0))
((0 . "LINE") (100 . "AcDbEntity") (8 . "MASONRY") (62 . 7) (370 . 13) (100 . "AcDbLine") (10 9888.7627375566
991.7052941176 0.0) (11 9898.1900452489 991.7052941176 0.0))
((0 . "LINE") (100 . "AcDbEntity") (8 . "MASONRY") (62 . 7) (370 . 13) (100 . "AcDbLine") (10 9901.9598642534
5520.3619909502 0.0) (11 9901.9598642534 5527.9030090498 0.0))
((0 . "LINE") (100 . "AcDbEntity") (8 . "MASONRY") (62 . 7) (370 . 13) (100 . "AcDbLine") (10 9898.1900452489
5478.884321267 0.0) (11 9898.1900452489 5439.2908710407 0.0))
((0 . "LINE") (100 . "AcDbEntity") (8 . "MASONRY") (62 . 7) (370 . 13) (100 . "AcDbLine") (10 10075.4157013575
5439.2908710407 0.0) (11 9898.1900452489 5439.2908710407 0.0))
((0 . "LINE") (100 . "AcDbEntity") (8 . "MASONRY") (62 . 7) (370 . 13) (100 . "AcDbLine") (10 9950.9813122172
5096.1538461538 0.0) (11 9898.1900452489 5096.1538461538 0.0))
((0 . "LINE") (100 . "AcDbEntity") (8 . "MASONRY") (62 . 7) (370 . 13) (100 . "AcDbLine") (10 9920.814479638
2835.5960067873 0.0) (11 9898.1900452489 2835.5960067873 0.0))
((0 . "LINE") (100 . "AcDbEntity") (8 . "MASONRY") (62 . 7) (370 . 13) (100 . "AcDbLine") (10 9928.3568778281
5527.9030090498 0.0) (11 9901.9598642534 5527.9030090498 0.0))
((0 . "LINE") (100 . "AcDbEntity") (8 . "MASONRY") (62 . 7) (370 . 13) (100 . "AcDbLine") (10 9901.9598642534
5550.5274434389 0.0) (11 9901.9598642534 5527.9030090498 0.0))
((0 . "LINE") (100 . "AcDbEntity") (8 . "MASONRY") (62 . 7) (370 . 13) (100 . "AcDbLine") (10 9901.9598642534
1259.4259276018 0.0) (11 9901.9598642534 1238.6877828054 0.0))
((0 . "LINE") (100 . "AcDbEntity") (8 . "MASONRY") (62 . 7) (370 . 13) (100 . "AcDbLine") (10 9901.9598642534
1259.4259276018 0.0) (11 9917.0446606335 1259.4259276018 0.0))
((0 . "LINE") (100 . "AcDbEntity") (8 . "MASONRY") (62 . 7) (370 . 13) (100 . "AcDbLine") (10 9913.272081448
1238.6877828054 0.0) (11 9901.9598642534 1238.6877828054 0.0))
((0 . "LINE") (100 . "AcDbEntity") (8 . "MASONRY") (62 . 7) (370 . 13) (100 . "AcDbLine") (10 9905.7324434389
4262.8202828054 0.0) (11 10018.8546153846 4262.8202828054 0.0))
((0 . "LINE") (100 . "AcDbEntity") (8 . "MASONRY") (62 . 7) (370 . 13) (100 . "AcDbLine") (10 9911.3871719457
810.7098190045 0.0) (11 9905.7324434389 810.7098190045 0.0))
((0 . "LINE") (100 . "AcDbEntity") (8 . "MASONRY") (62 . 7) (370 . 13) (100 . "AcDbLine") (10 9911.3871719457
4856.7123755656 0.0) (11 9911.3871719457 4892.5339366516 0.0))
((0 . "LINE") (100 . "AcDbEntity") (8 . "MASONRY") (62 . 7) (370 . 13) (100 . "AcDbLine") (10 9924.5842986425
3150.4524886878 0.0) (11 9909.5022624434 3150.4524886878 0.0))
((0 . "LINE") (100 . "AcDbEntity") (8 . "MASONRY") (62 . 7) (370 . 13) (100 . "AcDbLine") (10 9911.3871719457
810.7098190045 0.0) (11 9911.3871719457 848.4162895928 0.0))
((0 . "LINE") (100 . "AcDbEntity") (8 . "MASONRY") (62 . 7) (370 . 13) (100 . "AcDbLine") (10 9911.3871719457
848.4162895928 0.0) (11 10131.9767873303 848.4162895928 0.0))
((0 . "LINE") (100 . "AcDbEntity") (8 . "MASONRY") (62 . 7) (370 . 13) (100 . "AcDbLine") (10 9909.5022624434
573.1532579186 0.0) (11 9924.5842986425 573.1532579186 0.0))
((0 . "LINE") (100 . "AcDbEntity") (8 . "MASONRY") (62 . 7) (370 . 13) (100 . "AcDbLine") (10 10128.2042081448
4892.5339366516 0.0) (11 9911.3871719457 4892.5339366516 0.0))
((0 . "LINE") (100 . "AcDbEntity") (8 . "MASONRY") (62 . 7) (370 . 13) (100 . "AcDbLine") (10 9913.272081448
2334.0872511312 0.0) (11 10191.3659276018 2334.0872511312 0.0))
((0 . "LINE") (100 . "AcDbEntity") (8 . "MASONRY") (62 . 7) (370 . 13) (100 . "AcDbLine") (10 9911.3871719457
810.7098190045 0.0) (11 9992.45760181 810.7098190045 0.0))
((0 . "LINE") (100 . "AcDbEntity") (8 . "MASONRY") (62 . 7) (370 . 13) (100 . "AcDbLine") (10 9920.814479638
2835.5960067873 0.0) (11 9920.814479638 2767.7227036199 0.0))
((0 . "LINE") (100 . "AcDbEntity") (8 . "MASONRY") (62 . 7) (370 . 13) (100 . "AcDbLine") (10 9920.814479638
2835.5960067873 0.0) (11 9920.814479638 2944.946979638 0.0))
((0 . "LINE") (100 . "AcDbEntity") (8 . "MASONRY") (62 . 7) (370 . 13) (100 . "AcDbLine") (10 9993.0596719457
2767.7227036199 0.0) (11 9920.814479638 2767.7227036199 0.0))
((0 . "LINE") (100 . "AcDbEntity") (8 . "MASONRY") (62 . 7) (370 . 13) (100 . "AcDbLine") (10 9990.5726923077
2628.20489819 0.0) (11 9920.814479638 2628.20489819 0.0))
((0 . "LINE") (100 . "AcDbEntity") (8 . "MASONRY") (62 . 7) (370 . 13) (100 . "AcDbLine") (10 9920.814479638
1802.4137330317 0.0) (11 10150.8286425339 1802.4137330317 0.0))
((0 . "LINE") (100 . "AcDbEntity") (8 . "MASONRY") (62 . 7) (370 . 13) (100 . "AcDbLine") (10 10105.5797737557
2944.946979638 0.0) (11 9920.814479638 2944.946979638 0.0))
((0 . "LINE") (100 . "AcDbEntity") (8 . "MASONRY") (62 . 7) (370 . 13) (100 . "AcDbLine") (10 9924.5842986425
2269.9851470588 0.0) (11 9990.5726923077 2269.9851470588 0.0))
((0 . "LINE") (100 . "AcDbEntity") (8 . "MASONRY") (62 . 7) (370 . 13) (100 . "AcDbLine") (10 9937.7054751131
1987.1797171946 0.0) (11 9937.7054751131 1936.274739819 0.0))
((0 . "LINE") (100 . "AcDbEntity") (8 . "MASONRY") (62 . 7) (370 . 13) (100 . "AcDbLine") (10 9937.7054751131
1936.274739819 0.0) (11 9924.5842986425 1936.274739819 0.0))
((0 . "LINE") (100 . "AcDbEntity") (8 . "MASONRY") (62 . 7) (370 . 13) (100 . "AcDbLine") (10 9924.5842986425
955.8823529412 0.0) (11 9988.6877828054 955.8823529412 0.0))
((0 . "LINE") (100 . "AcDbEntity") (8 . "MASONRY") (62 . 7) (370 . 13) (100 . "AcDbLine") (10 9939.6690950226
1089.7426696833 0.0) (11 9932.1266968326 1089.7426696833 0.0))
((0 . "LINE") (100 . "AcDbEntity") (8 . "MASONRY") (62 . 7) (370 . 13) (100 . "AcDbLine") (10 9935.8965158371
3406.8622850679 0.0) (11 9992.45760181 3406.8622850679 0.0))
((0 . "LINE") (100 . "AcDbEntity") (8 . "MASONRY") (62 . 7) (370 . 13) (100 . "AcDbLine") (10 9981.1453846154
2405.7317533937 0.0) (11 9935.8965158371 2405.7317533937 0.0))
((0 . "LINE") (100 . "AcDbEntity") (8 . "MASONRY") (62 . 7) (370 . 13) (100 . "AcDbLine") (10 9937.7054751131
1987.1797171946 0.0) (11 9981.1453846154 1987.1797171946 0.0))
((0 . "LINE") (100 . "AcDbEntity") (8 . "MASONRY") (62 . 7) (370 . 13) (100 . "AcDbLine") (10 9996.2301809955
991.7052941176 0.0) (11 9935.8965158371 991.7052941176 0.0))
((0 . "LINE") (100 . "AcDbEntity") (8 . "MASONRY") (62 . 7) (370 . 13) (100 . "AcDbLine") (10 9941.5540045249
1858.9748190045 0.0) (11 9941.5540045249 1892.910780543 0.0))
((0 . "LINE") (100 . "AcDbEntity") (8 . "MASONRY") (62 . 7) (370 . 13) (100 . "AcDbLine") (10 9939.6690950226
1227.3755656109 0.0) (11 9954.7511312217 1227.3755656109 0.0))
((0 . "LINE") (100 . "AcDbEntity") (8 . "MASONRY") (62 . 7) (370 . 13) (100 . "AcDbLine") (10 9941.5540045249
1858.9748190045 0.0) (11 10154.6012217195 1858.9748190045 0.0))
((0 . "LINE") (100 . "AcDbEntity") (8 . "MASONRY") (62 . 7) (370 . 13) (100 . "AcDbLine") (10 9943.4389140272
86.7265384615 0.0) (11 9950.9813122172 86.7265384615 0.0))
((0 . "LINE") (100 . "AcDbEntity") (8 . "MASONRY") (62 . 7) (370 . 13) (100 . "AcDbLine") (10 9949.0950226244
4785.0678733032 0.0) (11 9949.0950226244 4769.9844570136 0.0))
((0 . "LINE") (100 . "AcDbEntity") (8 . "MASONRY") (62 . 7) (370 . 13) (100 . "AcDbLine") (10 10105.5797737557
1342.5310972851 0.0) (11 10086.727918552 1342.5310972851 0.0))
((0 . "LINE") (100 . "AcDbEntity") (8 . "MASONRY") (62 . 7) (370 . 13) (100 . "AcDbLine") (10 10086.727918552
1342.5310972851 0.0) (11 9947.2087330317 1342.5310972851 0.0))
((0 . "LINE") (100 . "AcDbEntity") (8 . "MASONRY") (62 . 7) (370 . 13) (100 . "AcDbLine") (10 9952.8689819005
177.2256561086 0.0) (11 9952.8689819005 121.2666402715 0.0))
((0 . "LINE") (100 . "AcDbEntity") (8 . "MASONRY") (62 . 7) (370 . 13) (100 . "AcDbLine") (10 9952.8689819005
121.2666402715 0.0) (11 10128.2042081448 121.2666402715 0.0))
((0 . "LINE") (100 . "AcDbEntity") (8 . "MASONRY") (62 . 7) (370 . 13) (100 . "AcDbLine") (10 9952.8689819005
177.2256561086 0.0) (11 10060.3309049774 177.2256561086 0.0))
((0 . "LINE") (100 . "AcDbEntity") (8 . "MASONRY") (62 . 7) (370 . 13) (100 . "AcDbLine") (10 9949.0950226244
4785.0678733032 0.0) (11 10148.9437330317 4785.0678733032 0.0))
((0 . "LINE") (100 . "AcDbEntity") (8 . "MASONRY") (62 . 7) (370 . 13) (100 . "AcDbLine") (10 10152.7149321267
1185.2958257919 0.0) (11 9971.2679072398 1185.2958257919 0.0))
((0 . "LINE") (100 . "AcDbEntity") (8 . "MASONRY") (62 . 7) (370 . 13) (100 . "AcDbLine") (10 9971.2679072398
1185.2958257919 0.0) (11 9971.2679072398 1099.1713574661 0.0))
((0 . "LINE") (100 . "AcDbEntity") (8 . "MASONRY") (62 . 7) (370 . 13) (100 . "AcDbLine") (10 9971.2679072398
1099.1713574661 0.0) (11 9950.9813122172 1099.1713574661 0.0))
((0 . "LINE") (100 . "AcDbEntity") (8 . "MASONRY") (62 . 7) (370 . 13) (100 . "AcDbLine") (10 9950.9813122172
575.0381674208 0.0) (11 9969.8331674208 575.0381674208 0.0))
((0 . "LINE") (100 . "AcDbEntity") (8 . "MASONRY") (62 . 7) (370 . 13) (100 . "AcDbLine") (10 9950.9813122172
256.4111764706 0.0) (11 9967.9482579186 256.4111764706 0.0))
((0 . "LINE") (100 . "AcDbEntity") (8 . "MASONRY") (62 . 7) (370 . 13) (100 . "AcDbLine") (10 9961.0093099548
5642.910780543 0.0) (11 9961.0093099548 5678.7330316742 0.0))
((0 . "LINE") (100 . "AcDbEntity") (8 . "MASONRY") (62 . 7) (370 . 13) (100 . "AcDbLine") (10 9961.0093099548
5678.7330316742 0.0) (11 9961.0093099548 5731.5232579186 0.0))
((0 . "LINE") (100 . "AcDbEntity") (8 . "MASONRY") (62 . 7) (370 . 13) (100 . "AcDbLine") (10 9966.0633484163
6114.2533936652 0.0) (11 9958.5209502262 6114.2533936652 0.0))
((0 . "LINE") (100 . "AcDbEntity") (8 . "MASONRY") (62 . 7) (370 . 13) (100 . "AcDbLine") (10 9958.5209502262
50.9049773756 0.0) (11 9966.0633484163 50.9049773756 0.0))
((0 . "LINE") (100 . "AcDbEntity") (8 . "MASONRY") (62 . 7) (370 . 13) (100 . "AcDbLine") (10 10248.8687782805
4973.6043665158 0.0) (11 9962.2935294118 4973.6043665158 0.0))
((0 . "LINE") (100 . "AcDbEntity") (8 . "MASONRY") (62 . 7) (370 . 13) (100 . "AcDbLine") (10 10196.0775113122
3707.9195701357 0.0) (11 9946.0039140272 3707.9195701357 0.0))
((0 . "LINE") (100 . "AcDbEntity") (8 . "MASONRY") (62 . 7) (370 . 13) (100 . "AcDbLine") (10 9946.0039140272
3707.9195701357 0.0) (11 9946.0039140272 3689.7453846154 0.0))
((0 . "LINE") (100 . "AcDbEntity") (8 . "MASONRY") (62 . 7) (370 . 13) (100 . "AcDbLine") (10 9946.0039140272
3689.7453846154 0.0) (11 9962.2935294118 3689.7453846154 0.0))
((0 . "LINE") (100 . "AcDbEntity") (8 . "MASONRY") (62 . 7) (370 . 13) (100 . "AcDbLine") (10 9966.0633484163
6114.2533936652 0.0) (11 9966.0633484163 6206.6363800905 0.0))
((0 . "LINE") (100 . "AcDbEntity") (8 . "MASONRY") (62 . 7) (370 . 13) (100 . "AcDbLine") (10 9998.1150904977
6206.6363800905 0.0) (11 9966.0633484163 6206.6363800905 0.0))
((0 . "LINE") (100 . "AcDbEntity") (8 . "MASONRY") (62 . 7) (370 . 13) (100 . "AcDbLine") (10 9966.0633484163
6114.2533936652 0.0) (11 9966.0633484163 6093.6754298643 0.0))
((0 . "LINE") (100 . "AcDbEntity") (8 . "MASONRY") (62 . 7) (370 . 13) (100 . "AcDbLine") (10 9966.0633484163
6093.6754298643 0.0) (11 10194.19260181 6093.6754298643 0.0))
((0 . "LINE") (100 . "AcDbEntity") (8 . "MASONRY") (62 . 7) (370 . 13) (100 . "AcDbLine") (10 9961.0093099548
5642.910780543 0.0) (11 9961.0093099548 5546.7576244344 0.0))
((0 . "LINE") (100 . "AcDbEntity") (8 . "MASONRY") (62 . 7) (370 . 13) (100 . "AcDbLine") (10 9961.0093099548
5546.7576244344 0.0) (11 9969.8331674208 5546.7576244344 0.0))
((0 . "LINE") (100 . "AcDbEntity") (8 . "MASONRY") (62 . 7) (370 . 13) (100 . "AcDbLine") (10 9969.8331674208
5546.7576244344 0.0) (11 10109.3509728507 5546.7576244344 0.0))
((0 . "LINE") (100 . "AcDbEntity") (8 . "MASONRY") (62 . 7) (370 . 13) (100 . "AcDbLine") (10 9961.0093099548
5642.910780543 0.0) (11 10056.5610859729 5642.910780543 0.0))
((0 . "LINE") (100 . "AcDbEntity") (8 . "MASONRY") (62 . 7) (370 . 13) (100 . "AcDbLine") (10 9969.8331674208
5199.8487104072 0.0) (11 9969.8331674208 5248.8687782805 0.0))
((0 . "LINE") (100 . "AcDbEntity") (8 . "MASONRY") (62 . 7) (370 . 13) (100 . "AcDbLine") (10 10022.6244343891
5248.8687782805 0.0) (11 9969.8331674208 5248.8687782805 0.0))
((0 . "LINE") (100 . "AcDbEntity") (8 . "MASONRY") (62 . 7) (370 . 13) (100 . "AcDbLine") (10 9969.8345475113
3159.8791063348 0.0) (11 9969.8345475113 3148.5668891403 0.0))
((0 . "LINE") (100 . "AcDbEntity") (8 . "MASONRY") (62 . 7) (370 . 13) (100 . "AcDbLine") (10 9966.0633484163
2865.761459276 0.0) (11 10128.2042081448 2865.761459276 0.0))
((0 . "LINE") (100 . "AcDbEntity") (8 . "MASONRY") (62 . 7) (370 . 13) (100 . "AcDbLine") (10 9969.8331674208
575.0381674208 0.0) (11 9969.8331674208 537.3303167421 0.0))
((0 . "LINE") (100 . "AcDbEntity") (8 . "MASONRY") (62 . 7) (370 . 13) (100 . "AcDbLine") (10 9969.8331674208
575.0381674208 0.0) (11 9969.8331674208 697.5876470588 0.0))
((0 . "LINE") (100 . "AcDbEntity") (8 . "MASONRY") (62 . 7) (370 . 13) (100 . "AcDbLine") (10 10098.0401357466
256.4111764706 0.0) (11 9967.9482579186 256.4111764706 0.0))
((0 . "LINE") (100 . "AcDbEntity") (8 . "MASONRY") (62 . 7) (370 . 13) (100 . "AcDbLine") (10 9967.9482579186
275.2630316742 0.0) (11 9967.9482579186 256.4111764706 0.0))
((0 . "LINE") (100 . "AcDbEntity") (8 . "MASONRY") (62 . 7) (370 . 13) (100 . "AcDbLine") (10 9969.8331674208
6255.6561085973 0.0) (11 9993.6624208145 6255.6561085973 0.0))
((0 . "LINE") (100 . "AcDbEntity") (8 . "MASONRY") (62 . 7) (370 . 13) (100 . "AcDbLine") (10 9971.7194570136
6014.3286877828 0.0) (11 10011.3122171946 6014.3286877828 0.0))
((0 . "LINE") (100 . "AcDbEntity") (8 . "MASONRY") (62 . 7) (370 . 13) (100 . "AcDbLine") (10 9971.7194570136
6014.3286877828 0.0) (11 9971.7194570136 6074.6606334842 0.0))
((0 . "LINE") (100 . "AcDbEntity") (8 . "MASONRY") (62 . 7) (370 . 13) (100 . "AcDbLine") (10 9969.8331674208
5199.8487104072 0.0) (11 9969.8331674208 5180.9954751131 0.0))
((0 . "LINE") (100 . "AcDbEntity") (8 . "MASONRY") (62 . 7) (370 . 13) (100 . "AcDbLine") (10 9969.8331674208
3563.3484162896 0.0) (11 9988.6877828054 3563.3484162896 0.0))
((0 . "LINE") (100 . "AcDbEntity") (8 . "MASONRY") (62 . 7) (370 . 13) (100 . "AcDbLine") (10 9981.1453846154
1606.334841629 0.0) (11 9981.1453846154 1591.2514253394 0.0))
((0 . "LINE") (100 . "AcDbEntity") (8 . "MASONRY") (62 . 7) (370 . 13) (100 . "AcDbLine") (10 9988.6877828054
5199.8487104072 0.0) (11 9969.8331674208 5199.8487104072 0.0))
((0 . "LINE") (100 . "AcDbEntity") (8 . "MASONRY") (62 . 7) (370 . 13) (100 . "AcDbLine") (10 9981.1467647059
2213.424061086 0.0) (11 9981.1467647059 2232.2772963801 0.0))
((0 . "LINE") (100 . "AcDbEntity") (8 . "MASONRY") (62 . 7) (370 . 13) (100 . "AcDbLine") (10 10165.913438914
537.3303167421 0.0) (11 9969.8331674208 537.3303167421 0.0))
((0 . "LINE") (100 . "AcDbEntity") (8 . "MASONRY") (62 . 7) (370 . 13) (100 . "AcDbLine") (10 9977.3755656109
4726.6211877828 0.0) (11 10011.3122171946 4726.6211877828 0.0))
((0 . "LINE") (100 . "AcDbEntity") (8 . "MASONRY") (62 . 7) (370 . 13) (100 . "AcDbLine") (10 9977.3755656109
4021.6416628959 0.0) (11 9977.3755656109 4030.920520362 0.0))
((0 . "LINE") (100 . "AcDbEntity") (8 . "MASONRY") (62 . 7) (370 . 13) (100 . "AcDbLine") (10 9977.3755656109
4021.6416628959 0.0) (11 10318.7788914027 4021.6416628959 0.0))
((0 . "LINE") (100 . "AcDbEntity") (8 . "MASONRY") (62 . 7) (370 . 13) (100 . "AcDbLine") (10 10318.7788914027
4021.6416628959 0.0) (11 10318.7788914027 3989.4414705882 0.0))
((0 . "LINE") (100 . "AcDbEntity") (8 . "MASONRY") (62 . 7) (370 . 13) (100 . "AcDbLine") (10 9977.3755656109
3684.0116063348 0.0) (11 9984.9179638009 3684.0116063348 0.0))
((0 . "LINE") (100 . "AcDbEntity") (8 . "MASONRY") (62 . 7) (370 . 13) (100 . "AcDbLine") (10 9983.0316742081
5064.1021040724 0.0) (11 9983.0316742081 4996.228800905 0.0))
((0 . "LINE") (100 . "AcDbEntity") (8 . "MASONRY") (62 . 7) (370 . 13) (100 . "AcDbLine") (10 9981.1453846154
2021.1163687783 0.0) (11 9981.1453846154 1987.1797171946 0.0))
((0 . "LINE") (100 . "AcDbEntity") (8 . "MASONRY") (62 . 7) (370 . 13) (100 . "AcDbLine") (10 9981.1453846154
1987.1797171946 0.0) (11 10041.4790497738 1987.1797171946 0.0))
((0 . "LINE") (100 . "AcDbEntity") (8 . "MASONRY") (62 . 7) (370 . 13) (100 . "AcDbLine") (10 9981.1453846154
1564.8557918552 0.0) (11 9981.1453846154 1591.2514253394 0.0))
((0 . "LINE") (100 . "AcDbEntity") (8 . "MASONRY") (62 . 7) (370 . 13) (100 . "AcDbLine") (10 9981.1453846154
1591.2514253394 0.0) (11 10124.4343891403 1591.2514253394 0.0))
((0 . "LINE") (100 . "AcDbEntity") (8 . "MASONRY") (62 . 7) (370 . 13) (100 . "AcDbLine") (10 9981.1453846154
1523.3795022624 0.0) (11 10064.1034841629 1523.3795022624 0.0))
((0 . "LINE") (100 . "AcDbEntity") (8 . "MASONRY") (62 . 7) (370 . 13) (100 . "AcDbLine") (10 9981.1453846154
1523.3795022624 0.0) (11 9981.1453846154 1515.8371040724 0.0))
((0 . "LINE") (100 . "AcDbEntity") (8 . "MASONRY") (62 . 7) (370 . 13) (100 . "AcDbLine") (10 9981.1453846154
1436.6515837104 0.0) (11 9981.1453846154 1493.2126696833 0.0))
((0 . "LINE") (100 . "AcDbEntity") (8 . "MASONRY") (62 . 7) (370 . 13) (100 . "AcDbLine") (10 9981.1453846154
1436.6515837104 0.0) (11 10071.6431221719 1436.6515837104 0.0))
((0 . "LINE") (100 . "AcDbEntity") (8 . "MASONRY") (62 . 7) (370 . 13) (100 . "AcDbLine") (10 9992.45760181
4566.3645475113 0.0) (11 9984.9179638009 4566.3645475113 0.0))
((0 . "LINE") (100 . "AcDbEntity") (8 . "MASONRY") (62 . 7) (370 . 13) (100 . "AcDbLine") (10 9984.9179638009
3672.6993891403 0.0) (11 9984.9179638009 3684.0116063348 0.0))
((0 . "LINE") (100 . "AcDbEntity") (8 . "MASONRY") (62 . 7) (370 . 13) (100 . "AcDbLine") (10 10018.8546153846
3684.0116063348 0.0) (11 9984.9179638009 3684.0116063348 0.0))
((0 . "LINE") (100 . "AcDbEntity") (8 . "MASONRY") (62 . 7) (370 . 13) (100 . "AcDbLine") (10 9988.6877828054
3597.2850678733 0.0) (11 9988.6877828054 3563.3484162896 0.0))
((0 . "LINE") (100 . "AcDbEntity") (8 . "MASONRY") (62 . 7) (370 . 13) (100 . "AcDbLine") (10 9988.6877828054
3597.2850678733 0.0) (11 9988.6877828054 3608.5972850679 0.0))
((0 . "LINE") (100 . "AcDbEntity") (8 . "MASONRY") (62 . 7) (370 . 13) (100 . "AcDbLine") (10 9996.2301809955
1266.9683257919 0.0) (11 9984.9179638009 1266.9683257919 0.0))
((0 . "LINE") (100 . "AcDbEntity") (8 . "MASONRY") (62 . 7) (370 . 13) (100 . "AcDbLine") (10 9993.6624208145
6255.6561085973 0.0) (11 9993.6624208145 6240.5730316742 0.0))
((0 . "LINE") (100 . "AcDbEntity") (8 . "MASONRY") (62 . 7) (370 . 13) (100 . "AcDbLine") (10 10267.7233936652
6308.3690158371 0.0) (11 10011.3122171946 6308.3690158371 0.0))
((0 . "LINE") (100 . "AcDbEntity") (8 . "MASONRY") (62 . 7) (370 . 13) (100 . "AcDbLine") (10 10011.3122171946
6308.3690158371 0.0) (11 9993.6624208145 6308.3690158371 0.0))
((0 . "LINE") (100 . "AcDbEntity") (8 . "MASONRY") (62 . 7) (370 . 13) (100 . "AcDbLine") (10 9993.6624208145
6308.3690158371 0.0) (11 9993.6624208145 6255.6561085973 0.0))
((0 . "LINE") (100 . "AcDbEntity") (8 . "MASONRY") (62 . 7) (370 . 13) (100 . "AcDbLine") (10 9992.45760181
4596.5313800905 0.0) (11 9992.45760181 4624.8112330317 0.0))
((0 . "LINE") (100 . "AcDbEntity") (8 . "MASONRY") (62 . 7) (370 . 13) (100 . "AcDbLine") (10 9988.6877828054
4234.5404298643 0.0) (11 9988.6877828054 4211.9159954751 0.0))
((0 . "LINE") (100 . "AcDbEntity") (8 . "MASONRY") (62 . 7) (370 . 13) (100 . "AcDbLine") (10 10022.6244343891
2628.20489819 0.0) (11 9990.5726923077 2628.20489819 0.0))
((0 . "LINE") (100 . "AcDbEntity") (8 . "MASONRY") (62 . 7) (370 . 13) (100 . "AcDbLine") (10 9990.5726923077
2677.2249660633 0.0) (11 9990.5726923077 2628.20489819 0.0))
((0 . "LINE") (100 . "AcDbEntity") (8 . "MASONRY") (62 . 7) (370 . 13) (100 . "AcDbLine") (10 9990.5726923077
2258.6729298643 0.0) (11 9990.5726923077 2269.9851470588 0.0))
((0 . "LINE") (100 . "AcDbEntity") (8 . "MASONRY") (62 . 7) (370 . 13) (100 . "AcDbLine") (10 10003.7698190045
2269.9851470588 0.0) (11 9990.5726923077 2269.9851470588 0.0))
((0 . "LINE") (100 . "AcDbEntity") (8 . "MASONRY") (62 . 7) (370 . 13) (100 . "AcDbLine") (10 9988.6877828054
2198.3406447964 0.0) (11 9988.6877828054 2175.7162104072 0.0))
((0 . "LINE") (100 . "AcDbEntity") (8 . "MASONRY") (62 . 7) (370 . 13) (100 . "AcDbLine") (10 9992.45760181
4634.2378506787 0.0) (11 9992.45760181 4679.486719457 0.0))
((0 . "LINE") (100 . "AcDbEntity") (8 . "MASONRY") (62 . 7) (370 . 13) (100 . "AcDbLine") (10 9992.45760181
4634.2378506787 0.0) (11 9992.45760181 4624.8112330317 0.0))
((0 . "LINE") (100 . "AcDbEntity") (8 . "MASONRY") (62 . 7) (370 . 13) (100 . "AcDbLine") (10 10139.5164253394
4211.9159954751 0.0) (11 9988.6877828054 4211.9159954751 0.0))
((0 . "LINE") (100 . "AcDbEntity") (8 . "MASONRY") (62 . 7) (370 . 13) (100 . "AcDbLine") (10 9988.6877828054
3563.3484162896 0.0) (11 10000 3563.3484162896 0.0))
((0 . "LINE") (100 . "AcDbEntity") (8 . "MASONRY") (62 . 7) (370 . 13) (100 . "AcDbLine") (10 9992.45760181
3288.0846945701 0.0) (11 9992.45760181 3325.7918552036 0.0))
((0 . "LINE") (100 . "AcDbEntity") (8 . "MASONRY") (62 . 7) (370 . 13) (100 . "AcDbLine") (10 10199.8500904977
3325.7918552036 0.0) (11 9992.45760181 3325.7918552036 0.0))
((0 . "LINE") (100 . "AcDbEntity") (8 . "MASONRY") (62 . 7) (370 . 13) (100 . "AcDbLine") (10 9992.45760181
3288.0846945701 0.0) (11 9992.45760181 3186.274739819 0.0))
((0 . "LINE") (100 . "AcDbEntity") (8 . "MASONRY") (62 . 7) (370 . 13) (100 . "AcDbLine") (10 9992.45760181
3288.0846945701 0.0) (11 10143.2890045249 3288.0846945701 0.0))
((0 . "LINE") (100 . "AcDbEntity") (8 . "MASONRY") (62 . 7) (370 . 13) (100 . "AcDbLine") (10 9993.0596719457
2767.7227036199 0.0) (11 9993.0596719457 2718.7799660633 0.0))
((0 . "LINE") (100 . "AcDbEntity") (8 . "MASONRY") (62 . 7) (370 . 13) (100 . "AcDbLine") (10 9993.0596719457
2718.7799660633 0.0) (11 10007.54239819 2718.7799660633 0.0))
((0 . "LINE") (100 . "AcDbEntity") (8 . "MASONRY") (62 . 7) (370 . 13) (100 . "AcDbLine") (10 10018.8546153846
2767.7227036199 0.0) (11 9993.0596719457 2767.7227036199 0.0))
((0 . "LINE") (100 . "AcDbEntity") (8 . "MASONRY") (62 . 7) (370 . 13) (100 . "AcDbLine") (10 9992.45760181
810.7098190045 0.0) (11 9992.45760181 754.1487330317 0.0))
((0 . "LINE") (100 . "AcDbEntity") (8 . "MASONRY") (62 . 7) (370 . 13) (100 . "AcDbLine") (10 9992.45760181
810.7098190045 0.0) (11 10124.4343891403 810.7098190045 0.0))
((0 . "LINE") (100 . "AcDbEntity") (8 . "MASONRY") (62 . 7) (370 . 13) (100 . "AcDbLine") (10 10218.7019457014
52.7912669683 0.0) (11 9992.45760181 52.7912669683 0.0))
((0 . "LINE") (100 . "AcDbEntity") (8 . "MASONRY") (62 . 7) (370 . 13) (100 . "AcDbLine") (10 9998.1150904977
6206.6363800905 0.0) (11 10203.6199095023 6206.6363800905 0.0))
((0 . "LINE") (100 . "AcDbEntity") (8 . "MASONRY") (62 . 7) (370 . 13) (100 . "AcDbLine") (10 9998.1150904977
6206.6363800905 0.0) (11 9998.1150904977 6217.9485972851 0.0))
((0 . "LINE") (100 . "AcDbEntity") (8 . "MASONRY") (62 . 7) (370 . 13) (100 . "AcDbLine") (10 10241.3263800905
4634.2378506787 0.0) (11 9992.45760181 4634.2378506787 0.0))
((0 . "LINE") (100 . "AcDbEntity") (8 . "MASONRY") (62 . 7) (370 . 13) (100 . "AcDbLine") (10 10005.6561085973
6331.0707692308 0.0) (11 10005.6561085973 6391.4027149321 0.0))
((0 . "LINE") (100 . "AcDbEntity") (8 . "MASONRY") (62 . 7) (370 . 13) (100 . "AcDbLine") (10 10005.6561085973
6391.4027149321 0.0) (11 10286.5752488688 6391.4027149321 0.0))
((0 . "LINE") (100 . "AcDbEntity") (8 . "MASONRY") (62 . 7) (370 . 13) (100 . "AcDbLine") (10 10007.54239819
5767.3451696833 0.0) (11 10113.1221719457 5767.3451696833 0.0))
((0 . "LINE") (100 . "AcDbEntity") (8 . "MASONRY") (62 . 7) (370 . 13) (100 . "AcDbLine") (10 10011.3122171946
3981.9004524887 0.0) (11 10105.5797737557 3981.9004524887 0.0))
((0 . "LINE") (100 . "AcDbEntity") (8 . "MASONRY") (62 . 7) (370 . 13) (100 . "AcDbLine") (10 10011.3122171946
1070.8908144796 0.0) (11 10069.7582126697 1070.8908144796 0.0))
((0 . "LINE") (100 . "AcDbEntity") (8 . "MASONRY") (62 . 7) (370 . 13) (100 . "AcDbLine") (10 10011.3122171946
991.7052941176 0.0) (11 10072.2451923077 991.7052941176 0.0))
((0 . "LINE") (100 . "AcDbEntity") (8 . "MASONRY") (62 . 7) (370 . 13) (100 . "AcDbLine") (10 10018.8532352941
5305.4298642534 0.0) (11 10018.8532352941 5316.742081448 0.0))
((0 . "LINE") (100 . "AcDbEntity") (8 . "MASONRY") (62 . 7) (370 . 13) (100 . "AcDbLine") (10 10022.6244343891
3408.7478846154 0.0) (11 10049.0186877828 3408.7478846154 0.0))
((0 . "LINE") (100 . "AcDbEntity") (8 . "MASONRY") (62 . 7) (370 . 13) (100 . "AcDbLine") (10 10026.3942533937
2405.7317533937 0.0) (11 10041.4790497738 2405.7317533937 0.0))
((0 . "LINE") (100 . "AcDbEntity") (8 . "MASONRY") (62 . 7) (370 . 13) (100 . "AcDbLine") (10 10067.8733031674
3682.1266968326 0.0) (11 10033.9366515837 3682.1266968326 0.0))
((0 . "LINE") (100 . "AcDbEntity") (8 . "MASONRY") (62 . 7) (370 . 13) (100 . "AcDbLine") (10 10033.9366515837
2518.8539253394 0.0) (11 10033.9366515837 2488.6877828054 0.0))
((0 . "LINE") (100 . "AcDbEntity") (8 . "MASONRY") (62 . 7) (370 . 13) (100 . "AcDbLine") (10 10033.9366515837
2518.8539253394 0.0) (11 10094.3455769231 2518.8539253394 0.0))
((0 . "LINE") (100 . "AcDbEntity") (8 . "MASONRY") (62 . 7) (370 . 13) (100 . "AcDbLine") (10 10109.3523529412
2269.9851470588 0.0) (11 10033.9366515837 2269.9851470588 0.0))
((0 . "LINE") (100 . "AcDbEntity") (8 . "MASONRY") (62 . 7) (370 . 13) (100 . "AcDbLine") (10 10109.3523529412
2168.1751923077 0.0) (11 10098.0401357466 2168.1751923077 0.0))
((0 . "LINE") (100 . "AcDbEntity") (8 . "MASONRY") (62 . 7) (370 . 13) (100 . "AcDbLine") (10 10098.0401357466
2168.1751923077 0.0) (11 10045.2488687783 2168.1751923077 0.0))
((0 . "LINE") (100 . "AcDbEntity") (8 . "MASONRY") (62 . 7) (370 . 13) (100 . "AcDbLine") (10 10045.2488687783
2168.1751923077 0.0) (11 10033.9366515837 2168.1751923077 0.0))
((0 . "LINE") (100 . "AcDbEntity") (8 . "MASONRY") (62 . 7) (370 . 13) (100 . "AcDbLine") (10 10131.9767873303
5953.9971040724 0.0) (11 10039.592760181 5953.9971040724 0.0))
((0 . "LINE") (100 . "AcDbEntity") (8 . "MASONRY") (62 . 7) (370 . 13) (100 . "AcDbLine") (10 10039.592760181
5953.9971040724 0.0) (11 10039.592760181 5987.9337556561 0.0))
((0 . "LINE") (100 . "AcDbEntity") (8 . "MASONRY") (62 . 7) (370 . 13) (100 . "AcDbLine") (10 10222.4745248869
3633.1073190045 0.0) (11 10037.7064705882 3633.1073190045 0.0))
((0 . "LINE") (100 . "AcDbEntity") (8 . "MASONRY") (62 . 7) (370 . 13) (100 . "AcDbLine") (10 10037.7064705882
2769.6083031674 0.0) (11 10071.6431221719 2769.6083031674 0.0))
((0 . "LINE") (100 . "AcDbEntity") (8 . "MASONRY") (62 . 7) (370 . 13) (100 . "AcDbLine") (10 10252.6385972851
2628.20489819 0.0) (11 10037.7064705882 2628.20489819 0.0))
((0 . "LINE") (100 . "AcDbEntity") (8 . "MASONRY") (62 . 7) (370 . 13) (100 . "AcDbLine") (10 10041.4790497738
4144.0426923077 0.0) (11 10280.920520362 4144.0426923077 0.0))
((0 . "LINE") (100 . "AcDbEntity") (8 . "MASONRY") (62 . 7) (370 . 13) (100 . "AcDbLine") (10 10120.6645701357
3186.274739819 0.0) (11 10041.4790497738 3186.274739819 0.0))
((0 . "LINE") (100 . "AcDbEntity") (8 . "MASONRY") (62 . 7) (370 . 13) (100 . "AcDbLine") (10 10196.0775113122
2720.5882352941 0.0) (11 10041.4790497738 2720.5882352941 0.0))
((0 . "LINE") (100 . "AcDbEntity") (8 . "MASONRY") (62 . 7) (370 . 13) (100 . "AcDbLine") (10 10052.7898868778
6018.0995475113 0.0) (11 10052.7898868778 5999.2459728507 0.0))
((0 . "LINE") (100 . "AcDbEntity") (8 . "MASONRY") (62 . 7) (370 . 13) (100 . "AcDbLine") (10 10148.9437330317
4724.7355882353 0.0) (11 10045.2488687783 4724.7355882353 0.0))
((0 . "LINE") (100 . "AcDbEntity") (8 . "MASONRY") (62 . 7) (370 . 13) (100 . "AcDbLine") (10 10045.2488687783
4249.6224660633 0.0) (11 10139.5164253394 4249.6224660633 0.0))
((0 . "LINE") (100 . "AcDbEntity") (8 . "MASONRY") (62 . 7) (370 . 13) (100 . "AcDbLine") (10 10056.5610859729
5252.6399773756 0.0) (11 10164.0271493213 5252.6399773756 0.0))
((0 . "LINE") (100 . "AcDbEntity") (8 . "MASONRY") (62 . 7) (370 . 13) (100 . "AcDbLine") (10 10060.3309049774
4370.2870361991 0.0) (11 10060.3309049774 4340.0435633484 0.0))
((0 . "LINE") (100 . "AcDbEntity") (8 . "MASONRY") (62 . 7) (370 . 13) (100 . "AcDbLine") (10 10395.92760181
4340.0435633484 0.0) (11 10060.3309049774 4340.0435633484 0.0))
((0 . "LINE") (100 . "AcDbEntity") (8 . "MASONRY") (62 . 7) (370 . 13) (100 . "AcDbLine") (10 10062.2171945701
4317.4957692308 0.0) (11 10062.2171945701 4287.3303167421 0.0))
((0 . "LINE") (100 . "AcDbEntity") (8 . "MASONRY") (62 . 7) (370 . 13) (100 . "AcDbLine") (10 10069.7582126697
1070.8908144796 0.0) (11 10069.7582126697 1059.5785972851 0.0))
((0 . "LINE") (100 . "AcDbEntity") (8 . "MASONRY") (62 . 7) (370 . 13) (100 . "AcDbLine") (10 10263.9508144796
1989.0653167421 0.0) (11 10071.6431221719 1989.0653167421 0.0))
((0 . "LINE") (100 . "AcDbEntity") (8 . "MASONRY") (62 . 7) (370 . 13) (100 . "AcDbLine") (10 10071.6431221719
1268.8532352941 0.0) (11 10101.8099547511 1268.8532352941 0.0))
((0 . "LINE") (100 . "AcDbEntity") (8 . "MASONRY") (62 . 7) (370 . 13) (100 . "AcDbLine") (10 10139.5164253394
1070.8908144796 0.0) (11 10069.7582126697 1070.8908144796 0.0))
((0 . "LINE") (100 . "AcDbEntity") (8 . "MASONRY") (62 . 7) (370 . 13) (100 . "AcDbLine") (10 10086.727918552
991.7052941176 0.0) (11 10072.2451923077 991.7052941176 0.0))
((0 . "LINE") (100 . "AcDbEntity") (8 . "MASONRY") (62 . 7) (370 . 13) (100 . "AcDbLine") (10 10086.727918552
955.8823529412 0.0) (11 10072.2451923077 955.8823529412 0.0))
((0 . "LINE") (100 . "AcDbEntity") (8 . "MASONRY") (62 . 7) (370 . 13) (100 . "AcDbLine") (10 10072.2451923077
955.8823529412 0.0) (11 10072.2451923077 991.7052941176 0.0))
((0 . "LINE") (100 . "AcDbEntity") (8 . "MASONRY") (62 . 7) (370 . 13) (100 . "AcDbLine") (10 10082.9553393665
1440.4214027149 0.0) (11 10343.1363348416 1440.4214027149 0.0))
((0 . "LINE") (100 . "AcDbEntity") (8 . "MASONRY") (62 . 7) (370 . 13) (100 . "AcDbLine") (10 10124.4343891403
177.2256561086 0.0) (11 10082.9553393665 177.2256561086 0.0))
((0 . "LINE") (100 . "AcDbEntity") (8 . "MASONRY") (62 . 7) (370 . 13) (100 . "AcDbLine") (10 10086.727918552
3548.2656900452 0.0) (11 10105.5797737557 3548.2656900452 0.0))
((0 . "LINE") (100 . "AcDbEntity") (8 . "MASONRY") (62 . 7) (370 . 13) (100 . "AcDbLine") (10 10086.727918552
3408.7478846154 0.0) (11 10124.4343891403 3408.7478846154 0.0))
((0 . "LINE") (100 . "AcDbEntity") (8 . "MASONRY") (62 . 7) (370 . 13) (100 . "AcDbLine") (10 10191.3659276018
2405.7317533937 0.0) (11 10086.727918552 2405.7317533937 0.0))
((0 . "LINE") (100 . "AcDbEntity") (8 . "MASONRY") (62 . 7) (370 . 13) (100 . "AcDbLine") (10 10150.8286425339
2518.8539253394 0.0) (11 10094.3455769231 2518.8539253394 0.0))
((0 . "LINE") (100 . "AcDbEntity") (8 . "MASONRY") (62 . 7) (370 . 13) (100 . "AcDbLine") (10 10094.3455769231
2518.8539253394 0.0) (11 10094.3455769231 2563.5007239819 0.0))
((0 . "LINE") (100 . "AcDbEntity") (8 . "MASONRY") (62 . 7) (370 . 13) (100 . "AcDbLine") (10 10094.3455769231
2563.5007239819 0.0) (11 10150.8286425339 2563.5007239819 0.0))
((0 . "LINE") (100 . "AcDbEntity") (8 . "MASONRY") (62 . 7) (370 . 13) (100 . "AcDbLine") (10 10094.2675565611
1523.3795022624 0.0) (11 10335.5966968326 1523.3795022624 0.0))
((0 . "LINE") (100 . "AcDbEntity") (8 . "MASONRY") (62 . 7) (370 . 13) (100 . "AcDbLine") (10 10335.5966968326
1523.3795022624 0.0) (11 10388.3852036199 1523.3795022624 0.0))
((0 . "LINE") (100 . "AcDbEntity") (8 . "MASONRY") (62 . 7) (370 . 13) (100 . "AcDbLine") (10 10098.0401357466
354.4485520362 0.0) (11 10131.9767873303 354.4485520362 0.0))
((0 . "LINE") (100 . "AcDbEntity") (8 . "MASONRY") (62 . 7) (370 . 13) (100 . "AcDbLine") (10 10098.0401357466
354.4485520362 0.0) (11 10098.0401357466 418.5520361991 0.0))
((0 . "LINE") (100 . "AcDbEntity") (8 . "MASONRY") (62 . 7) (370 . 13) (100 . "AcDbLine") (10 10101.8099547511
3046.7569343891 0.0) (11 10101.8099547511 3058.0691515837 0.0))
((0 . "LINE") (100 . "AcDbEntity") (8 . "MASONRY") (62 . 7) (370 . 13) (100 . "AcDbLine") (10 10098.0401357466
429.8642533937 0.0) (11 10098.0401357466 418.5520361991 0.0))
((0 . "LINE") (100 . "AcDbEntity") (8 . "MASONRY") (62 . 7) (370 . 13) (100 . "AcDbLine") (10 10101.8099547511
6025.6409049774 0.0) (11 10194.19260181 6025.6409049774 0.0))
((0 . "LINE") (100 . "AcDbEntity") (8 . "MASONRY") (62 . 7) (370 . 13) (100 . "AcDbLine") (10 10103.6948642534
5889.8942986425 0.0) (11 10103.6948642534 5897.4360180995 0.0))
((0 . "LINE") (100 . "AcDbEntity") (8 . "MASONRY") (62 . 7) (370 . 13) (100 . "AcDbLine") (10 10109.3509728507
5546.7576244344 0.0) (11 10237.556561086 5546.7576244344 0.0))
((0 . "LINE") (100 . "AcDbEntity") (8 . "MASONRY") (62 . 7) (370 . 13) (100 . "AcDbLine") (10 10109.3509728507
5546.7576244344 0.0) (11 10109.3509728507 5602.1912217195 0.0))
((0 . "LINE") (100 . "AcDbEntity") (8 . "MASONRY") (62 . 7) (370 . 13) (100 . "AcDbLine") (10 10109.3509728507
5602.1912217195 0.0) (11 10237.556561086 5602.1912217195 0.0))
((0 . "LINE") (100 . "AcDbEntity") (8 . "MASONRY") (62 . 7) (370 . 13) (100 . "AcDbLine") (10 10105.5797737557
2944.946979638 0.0) (11 10238.8394004525 2944.946979638 0.0))
((0 . "LINE") (100 . "AcDbEntity") (8 . "MASONRY") (62 . 7) (370 . 13) (100 . "AcDbLine") (10 10105.5797737557
3007.1648642534 0.0) (11 10105.5797737557 2944.946979638 0.0))
((0 . "LINE") (100 . "AcDbEntity") (8 . "MASONRY") (62 . 7) (370 . 13) (100 . "AcDbLine") (10 10211.1623076923
418.5520361991 0.0) (11 10098.0401357466 418.5520361991 0.0))
((0 . "LINE") (100 . "AcDbEntity") (8 . "MASONRY") (62 . 7) (370 . 13) (100 . "AcDbLine") (10 10105.5797737557
5833.3332126697 0.0) (11 10105.5797737557 5855.9576470588 0.0))
((0 . "LINE") (100 . "AcDbEntity") (8 . "MASONRY") (62 . 7) (370 . 13) (100 . "AcDbLine") (10 10105.5797737557
5833.3332126697 0.0) (11 10124.4343891403 5833.3332126697 0.0))
((0 . "LINE") (100 . "AcDbEntity") (8 . "MASONRY") (62 . 7) (370 . 13) (100 . "AcDbLine") (10 10107.4336085973
5629.7133031674 0.0) (11 10107.4336085973 5643.6626696833 0.0))
((0 . "LINE") (100 . "AcDbEntity") (8 . "MASONRY") (62 . 7) (370 . 13) (100 . "AcDbLine") (10 10107.4336085973
5643.6626696833 0.0) (11 10164.5546493213 5643.6626696833 0.0))
((0 . "LINE") (100 . "AcDbEntity") (8 . "MASONRY") (62 . 7) (370 . 13) (100 . "AcDbLine") (10 10173.4530769231
3472.850678733 0.0) (11 10111.2358823529 3472.850678733 0.0))
((0 . "LINE") (100 . "AcDbEntity") (8 . "MASONRY") (62 . 7) (370 . 13) (100 . "AcDbLine") (10 10241.3263800905
3506.6326696833 0.0) (11 10111.2358823529 3506.6326696833 0.0))
((0 . "LINE") (100 . "AcDbEntity") (8 . "MASONRY") (62 . 7) (370 . 13) (100 . "AcDbLine") (10 10111.2358823529
3506.6326696833 0.0) (11 10111.2358823529 3472.850678733 0.0))
((0 . "LINE") (100 . "AcDbEntity") (8 . "MASONRY") (62 . 7) (370 . 13) (100 . "AcDbLine") (10 10105.5797737557
3007.1648642534 0.0) (11 10105.5797737557 3020.3619909502 0.0))
((0 . "LINE") (100 . "AcDbEntity") (8 . "MASONRY") (62 . 7) (370 . 13) (100 . "AcDbLine") (10 10105.5797737557
2771.4932126697 0.0) (11 10245.0975791855 2771.4932126697 0.0))
((0 . "LINE") (100 . "AcDbEntity") (8 . "MASONRY") (62 . 7) (370 . 13) (100 . "AcDbLine") (10 10105.5797737557
3007.1648642534 0.0) (11 10124.4343891403 3007.1648642534 0.0))
((0 . "LINE") (100 . "AcDbEntity") (8 . "MASONRY") (62 . 7) (370 . 13) (100 . "AcDbLine") (10 10109.3523529412
2168.1751923077 0.0) (11 10282.8012895928 2168.1751923077 0.0))
((0 . "LINE") (100 . "AcDbEntity") (8 . "MASONRY") (62 . 7) (370 . 13) (100 . "AcDbLine") (10 10282.8012895928
2168.1751923077 0.0) (11 10282.8012895928 2194.5701357466 0.0))
((0 . "LINE") (100 . "AcDbEntity") (8 . "MASONRY") (62 . 7) (370 . 13) (100 . "AcDbLine") (10 10109.3523529412
991.7052941176 0.0) (11 10143.2890045249 991.7052941176 0.0))
((0 . "LINE") (100 . "AcDbEntity") (8 . "MASONRY") (62 . 7) (370 . 13) (100 . "AcDbLine") (10 10113.1221719457
5441.1764705882 0.0) (11 10192.3076923077 5441.1764705882 0.0))
((0 . "LINE") (100 . "AcDbEntity") (8 . "MASONRY") (62 . 7) (370 . 13) (100 . "AcDbLine") (10 10118.778280543
4517.3458597285 0.0) (11 10118.778280543 4477.829739819 0.0))
((0 . "LINE") (100 . "AcDbEntity") (8 . "MASONRY") (62 . 7) (370 . 13) (100 . "AcDbLine") (10 10118.778280543
4477.829739819 0.0) (11 10312.9722624434 4477.829739819 0.0))
((0 . "LINE") (100 . "AcDbEntity") (8 . "MASONRY") (62 . 7) (370 . 13) (100 . "AcDbLine") (10 10118.778280543
4517.3458597285 0.0) (11 10339.3665158371 4517.3458597285 0.0))
((0 . "LINE") (100 . "AcDbEntity") (8 . "MASONRY") (62 . 7) (370 . 13) (100 . "AcDbLine") (10 10124.4343891403
1342.3840271493 0.0) (11 10150.9839932127 1342.3840271493 0.0))
((0 . "LINE") (100 . "AcDbEntity") (8 . "MASONRY") (62 . 7) (370 . 13) (100 . "AcDbLine") (10 10128.2042081448
4924.585678733 0.0) (11 10128.2042081448 4892.5339366516 0.0))
((0 . "LINE") (100 . "AcDbEntity") (8 . "MASONRY") (62 . 7) (370 . 13) (100 . "AcDbLine") (10 10243.2126696833
4892.5339366516 0.0) (11 10128.2042081448 4892.5339366516 0.0))
((0 . "LINE") (100 . "AcDbEntity") (8 . "MASONRY") (62 . 7) (370 . 13) (100 . "AcDbLine") (10 10191.3659276018
2269.9851470588 0.0) (11 10128.2042081448 2269.9851470588 0.0))
((0 . "LINE") (100 . "AcDbEntity") (8 . "MASONRY") (62 . 7) (370 . 13) (100 . "AcDbLine") (10 10128.2042081448
1689.2901809955 0.0) (11 10128.2042081448 1676.0930542986 0.0))
((0 . "LINE") (100 . "AcDbEntity") (8 . "MASONRY") (62 . 7) (370 . 13) (100 . "AcDbLine") (10 10128.2042081448
1676.0930542986 0.0) (11 10180.9954751131 1676.0930542986 0.0))
((0 . "LINE") (100 . "AcDbEntity") (8 . "MASONRY") (62 . 7) (370 . 13) (100 . "AcDbLine") (10 10131.9767873303
3989.4414705882 0.0) (11 10318.7788914027 3989.4414705882 0.0))
((0 . "LINE") (100 . "AcDbEntity") (8 . "MASONRY") (62 . 7) (370 . 13) (100 . "AcDbLine") (10 10131.9767873303
1730.7692307692 0.0) (11 10197.963800905 1730.7692307692 0.0))
((0 . "LINE") (100 . "AcDbEntity") (8 . "MASONRY") (62 . 7) (370 . 13) (100 . "AcDbLine") (10 10131.9767873303
248.8687782805 0.0) (11 10131.9767873303 260.1809954751 0.0))
((0 . "LINE") (100 . "AcDbEntity") (8 . "MASONRY") (62 . 7) (370 . 13) (100 . "AcDbLine") (10 10131.9767873303
260.1809954751 0.0) (11 10131.9767873303 354.4485520362 0.0))
((0 . "LINE") (100 . "AcDbEntity") (8 . "MASONRY") (62 . 7) (370 . 13) (100 . "AcDbLine") (10 10131.9767873303
354.4485520362 0.0) (11 10354.4485520362 354.4485520362 0.0))
((0 . "LINE") (100 . "AcDbEntity") (8 . "MASONRY") (62 . 7) (370 . 13) (100 . "AcDbLine") (10 10139.5164253394
4211.9159954751 0.0) (11 10139.5164253394 4249.6224660633 0.0))
((0 . "LINE") (100 . "AcDbEntity") (8 . "MASONRY") (62 . 7) (370 . 13) (100 . "AcDbLine") (10 10165.913438914
4249.6224660633 0.0) (11 10139.5164253394 4249.6224660633 0.0))
((0 . "LINE") (100 . "AcDbEntity") (8 . "MASONRY") (62 . 7) (370 . 13) (100 . "AcDbLine") (10 10139.5164253394
4211.9159954751 0.0) (11 10279.0342307692 4211.9159954751 0.0))
((0 . "LINE") (100 . "AcDbEntity") (8 . "MASONRY") (62 . 7) (370 . 13) (100 . "AcDbLine") (10 10279.0342307692
4211.9159954751 0.0) (11 10279.0342307692 4230.7692307692 0.0))
((0 . "LINE") (100 . "AcDbEntity") (8 . "MASONRY") (62 . 7) (370 . 13) (100 . "AcDbLine") (10 10143.2876244344
3925.3393665158 0.0) (11 10143.2876244344 3951.735 0.0))
((0 . "LINE") (100 . "AcDbEntity") (8 . "MASONRY") (62 . 7) (370 . 13) (100 . "AcDbLine") (10 10143.2876244344
3863.1221719457 0.0) (11 10143.2876244344 3883.8616968326 0.0))
((0 . "LINE") (100 . "AcDbEntity") (8 . "MASONRY") (62 . 7) (370 . 13) (100 . "AcDbLine") (10 10167.7983484163
3186.274739819 0.0) (11 10143.2890045249 3186.274739819 0.0))
((0 . "LINE") (100 . "AcDbEntity") (8 . "MASONRY") (62 . 7) (370 . 13) (100 . "AcDbLine") (10 10148.9437330317
4724.7355882353 0.0) (11 10148.9437330317 4785.0678733032 0.0))
((0 . "LINE") (100 . "AcDbEntity") (8 . "MASONRY") (62 . 7) (370 . 13) (100 . "AcDbLine") (10 10148.9437330317
4796.3800904977 0.0) (11 10148.9437330317 4785.0678733032 0.0))
((0 . "LINE") (100 . "AcDbEntity") (8 . "MASONRY") (62 . 7) (370 . 13) (100 . "AcDbLine") (10 10388.3852036199
4724.7355882353 0.0) (11 10148.9437330317 4724.7355882353 0.0))
((0 . "LINE") (100 . "AcDbEntity") (8 . "MASONRY") (62 . 7) (370 . 13) (100 . "AcDbLine") (10 10143.2876244344
3863.1221719457 0.0) (11 10196.0775113122 3863.1221719457 0.0))
((0 . "LINE") (100 . "AcDbEntity") (8 . "MASONRY") (62 . 7) (370 . 13) (100 . "AcDbLine") (10 10173.4510067873
131.9767873303 0.0) (11 10173.4510067873 119.4549095023 0.0))
((0 . "LINE") (100 . "AcDbEntity") (8 . "MASONRY") (62 . 7) (370 . 13) (100 . "AcDbLine") (10 10173.4510067873
119.4549095023 0.0) (11 10147.0588235294 119.4549095023 0.0))
((0 . "LINE") (100 . "AcDbEntity") (8 . "MASONRY") (62 . 7) (370 . 13) (100 . "AcDbLine") (10 10177.2256561086
5211.1609276018 0.0) (11 10150.8286425339 5211.1609276018 0.0))
((0 . "LINE") (100 . "AcDbEntity") (8 . "MASONRY") (62 . 7) (370 . 13) (100 . "AcDbLine") (10 10154.599841629
4841.628959276 0.0) (11 10154.599841629 4856.7123755656 0.0))
((0 . "LINE") (100 . "AcDbEntity") (8 . "MASONRY") (62 . 7) (370 . 13) (100 . "AcDbLine") (10 10148.9437330317
4796.3800904977 0.0) (11 10148.9437330317 4819.0045248869 0.0))
((0 . "LINE") (100 . "AcDbEntity") (8 . "MASONRY") (62 . 7) (370 . 13) (100 . "AcDbLine") (10 10248.875678733
3061.8403506787 0.0) (11 10150.8286425339 3061.8403506787 0.0))
((0 . "LINE") (100 . "AcDbEntity") (8 . "MASONRY") (62 . 7) (370 . 13) (100 . "AcDbLine") (10 10150.8286425339
2518.8539253394 0.0) (11 10150.8286425339 2563.5007239819 0.0))
((0 . "LINE") (100 . "AcDbEntity") (8 . "MASONRY") (62 . 7) (370 . 13) (100 . "AcDbLine") (10 10150.8286425339
2575.4150113122 0.0) (11 10150.8286425339 2563.5007239819 0.0))
((0 . "LINE") (100 . "AcDbEntity") (8 . "MASONRY") (62 . 7) (370 . 13) (100 . "AcDbLine") (10 10150.8286425339
2518.8539253394 0.0) (11 10191.3659276018 2518.8539253394 0.0))
((0 . "LINE") (100 . "AcDbEntity") (8 . "MASONRY") (62 . 7) (370 . 13) (100 . "AcDbLine") (10 10392.1577828054
1263.3517873303 0.0) (11 10339.3665158371 1263.3517873303 0.0))
((0 . "LINE") (100 . "AcDbEntity") (8 . "MASONRY") (62 . 7) (370 . 13) (100 . "AcDbLine") (10 10339.3665158371
1263.3517873303 0.0) (11 10150.9839932127 1263.3517873303 0.0))
((0 . "LINE") (100 . "AcDbEntity") (8 . "MASONRY") (62 . 7) (370 . 13) (100 . "AcDbLine") (10 10150.9839932127
1263.3517873303 0.0) (11 10150.9839932127 1274.5107239819 0.0))
((0 . "LINE") (100 . "AcDbEntity") (8 . "MASONRY") (62 . 7) (370 . 13) (100 . "AcDbLine") (10 10150.9839932127
1274.5107239819 0.0) (11 10150.9839932127 1342.3840271493 0.0))
((0 . "LINE") (100 . "AcDbEntity") (8 . "MASONRY") (62 . 7) (370 . 13) (100 . "AcDbLine") (10 10165.913438914
1342.3840271493 0.0) (11 10150.9839932127 1342.3840271493 0.0))
((0 . "LINE") (100 . "AcDbEntity") (8 . "MASONRY") (62 . 7) (370 . 13) (100 . "AcDbLine") (10 10152.7149321267
1185.2958257919 0.0) (11 10152.7149321267 1233.0316742081 0.0))
((0 . "LINE") (100 . "AcDbEntity") (8 . "MASONRY") (62 . 7) (370 . 13) (100 . "AcDbLine") (10 10316.742081448
177.2256561086 0.0) (11 10150.8286425339 177.2256561086 0.0))
((0 . "LINE") (100 . "AcDbEntity") (8 . "MASONRY") (62 . 7) (370 . 13) (100 . "AcDbLine") (10 10148.9437330317
4796.3800904977 0.0) (11 10162.1408597285 4796.3800904977 0.0))
((0 . "LINE") (100 . "AcDbEntity") (8 . "MASONRY") (62 . 7) (370 . 13) (100 . "AcDbLine") (10 10152.7149321267
1185.2958257919 0.0) (11 10290.34989819 1185.2958257919 0.0))
((0 . "LINE") (100 . "AcDbEntity") (8 . "MASONRY") (62 . 7) (370 . 13) (100 . "AcDbLine") (10 10158.371040724
5946.4553846154 0.0) (11 10250.7550678733 5946.4553846154 0.0))
((0 . "LINE") (100 . "AcDbEntity") (8 . "MASONRY") (62 . 7) (370 . 13) (100 . "AcDbLine") (10 10388.3852036199 5846.0025
0.0) (11 10166.9622171946 5846.0025 0.0))
((0 . "LINE") (100 . "AcDbEntity") (8 . "MASONRY") (62 . 7) (370 . 13) (100 . "AcDbLine") (10 10166.9622171946 5846.0025
0.0) (11 10166.9622171946 5822.0209954751 0.0))
((0 . "LINE") (100 . "AcDbEntity") (8 . "MASONRY") (62 . 7) (370 . 13) (100 . "AcDbLine") (10 10166.9622171946
5822.0209954751 0.0) (11 10166.9622171946 5765.4599095023 0.0))
((0 . "LINE") (100 . "AcDbEntity") (8 . "MASONRY") (62 . 7) (370 . 13) (100 . "AcDbLine") (10 10158.371040724
4402.3380882353 0.0) (11 10246.9838687783 4402.3380882353 0.0))
((0 . "LINE") (100 . "AcDbEntity") (8 . "MASONRY") (62 . 7) (370 . 13) (100 . "AcDbLine") (10 10158.371040724
3009.0497737557 0.0) (11 10196.0775113122 3009.0497737557 0.0))
((0 . "LINE") (100 . "AcDbEntity") (8 . "MASONRY") (62 . 7) (370 . 13) (100 . "AcDbLine") (10 10164.5546493213
5643.6626696833 0.0) (11 10207.3897285068 5643.6626696833 0.0))
((0 . "LINE") (100 . "AcDbEntity") (8 . "MASONRY") (62 . 7) (370 . 13) (100 . "AcDbLine") (10 10345.0226244344
5727.752760181 0.0) (11 10164.5546493213 5727.752760181 0.0))
((0 . "LINE") (100 . "AcDbEntity") (8 . "MASONRY") (62 . 7) (370 . 13) (100 . "AcDbLine") (10 10164.5546493213
5727.752760181 0.0) (11 10164.5546493213 5643.6626696833 0.0))
((0 . "LINE") (100 . "AcDbEntity") (8 . "MASONRY") (62 . 7) (370 . 13) (100 . "AcDbLine") (10 10162.1408597285
5335.5960067873 0.0) (11 10184.7652941176 5335.5960067873 0.0))
((0 . "LINE") (100 . "AcDbEntity") (8 . "MASONRY") (62 . 7) (370 . 13) (100 . "AcDbLine") (10 10164.0271493213
5305.4298642534 0.0) (11 10164.0271493213 5252.6399773756 0.0))
((0 . "LINE") (100 . "AcDbEntity") (8 . "MASONRY") (62 . 7) (370 . 13) (100 . "AcDbLine") (10 10162.1408597285
3406.8622850679 0.0) (11 10173.4530769231 3406.8622850679 0.0))
((0 . "LINE") (100 . "AcDbEntity") (8 . "MASONRY") (62 . 7) (370 . 13) (100 . "AcDbLine") (10 10162.1408597285
3276.927138009 0.0) (11 10177.2256561086 3276.927138009 0.0))
((0 . "LINE") (100 . "AcDbEntity") (8 . "MASONRY") (62 . 7) (370 . 13) (100 . "AcDbLine") (10 10177.2256561086
3276.927138009 0.0) (11 10312.9722624434 3276.927138009 0.0))
((0 . "LINE") (100 . "AcDbEntity") (8 . "MASONRY") (62 . 7) (370 . 13) (100 . "AcDbLine") (10 10196.0775113122
2865.761459276 0.0) (11 10162.1408597285 2865.761459276 0.0))
((0 . "LINE") (100 . "AcDbEntity") (8 . "MASONRY") (62 . 7) (370 . 13) (100 . "AcDbLine") (10 10162.1408597285
986.0478054299 0.0) (11 10184.7652941176 986.0478054299 0.0))
((0 . "LINE") (100 . "AcDbEntity") (8 . "MASONRY") (62 . 7) (370 . 13) (100 . "AcDbLine") (10 10162.1408597285
889.8953393665 0.0) (11 10162.1408597285 923.8319909502 0.0))
((0 . "LINE") (100 . "AcDbEntity") (8 . "MASONRY") (62 . 7) (370 . 13) (100 . "AcDbLine") (10 10211.1623076923
855.9573076923 0.0) (11 10162.1408597285 855.9573076923 0.0))
((0 . "LINE") (100 . "AcDbEntity") (8 . "MASONRY") (62 . 7) (370 . 13) (100 . "AcDbLine") (10 10164.0271493213
690.0452488688 0.0) (11 10164.0271493213 618.4021266968 0.0))
((0 . "LINE") (100 . "AcDbEntity") (8 . "MASONRY") (62 . 7) (370 . 13) (100 . "AcDbLine") (10 10388.3852036199
5252.6399773756 0.0) (11 10164.0271493213 5252.6399773756 0.0))
((0 . "LINE") (100 . "AcDbEntity") (8 . "MASONRY") (62 . 7) (370 . 13) (100 . "AcDbLine") (10 10167.7983484163
3186.274739819 0.0) (11 10167.7983484163 3197.5869570136 0.0))
((0 . "LINE") (100 . "AcDbEntity") (8 . "MASONRY") (62 . 7) (370 . 13) (100 . "AcDbLine") (10 10165.913438914
948.3413348416 0.0) (11 10222.4745248869 948.3413348416 0.0))
((0 . "LINE") (100 . "AcDbEntity") (8 . "MASONRY") (62 . 7) (370 . 13) (100 . "AcDbLine") (10 10165.913438914
565.6108597285 0.0) (11 10165.913438914 537.3303167421 0.0))
((0 . "LINE") (100 . "AcDbEntity") (8 . "MASONRY") (62 . 7) (370 . 13) (100 . "AcDbLine") (10 10165.913438914
537.3303167421 0.0) (11 10324.284479638 537.3303167421 0.0))
((0 . "LINE") (100 . "AcDbEntity") (8 . "MASONRY") (62 . 7) (370 . 13) (100 . "AcDbLine") (10 10173.4530769231
3363.4990158371 0.0) (11 10173.4530769231 3406.8622850679 0.0))
((0 . "LINE") (100 . "AcDbEntity") (8 . "MASONRY") (62 . 7) (370 . 13) (100 . "AcDbLine") (10 10173.4530769231
3472.850678733 0.0) (11 10173.4530769231 3406.8622850679 0.0))
((0 . "LINE") (100 . "AcDbEntity") (8 . "MASONRY") (62 . 7) (370 . 13) (100 . "AcDbLine") (10 10167.7983484163
3186.274739819 0.0) (11 10250.7536877828 3186.274739819 0.0))
((0 . "LINE") (100 . "AcDbEntity") (8 . "MASONRY") (62 . 7) (370 . 13) (100 . "AcDbLine") (10 10184.7652941176
986.0478054299 0.0) (11 10184.7652941176 976.6204977376 0.0))
((0 . "LINE") (100 . "AcDbEntity") (8 . "MASONRY") (62 . 7) (370 . 13) (100 . "AcDbLine") (10 10184.7652941176
1004.9024208145 0.0) (11 10184.7652941176 986.0478054299 0.0))
((0 . "LINE") (100 . "AcDbEntity") (8 . "MASONRY") (62 . 7) (370 . 13) (100 . "AcDbLine") (10 10173.4530769231
3472.850678733 0.0) (11 10241.3263800905 3472.850678733 0.0))
((0 . "LINE") (100 . "AcDbEntity") (8 . "MASONRY") (62 . 7) (370 . 13) (100 . "AcDbLine") (10 10173.4530769231
1864.6309276018 0.0) (11 10199.8500904977 1864.6309276018 0.0))
((0 . "LINE") (100 . "AcDbEntity") (8 . "MASONRY") (62 . 7) (370 . 13) (100 . "AcDbLine") (10 10173.4530769231
1632.7290950226 0.0) (11 10173.4530769231 1640.2714932127 0.0))
((0 . "LINE") (100 . "AcDbEntity") (8 . "MASONRY") (62 . 7) (370 . 13) (100 . "AcDbLine") (10 10173.4530769231
1595.0226244344 0.0) (11 10348.7924434389 1595.0226244344 0.0))
((0 . "LINE") (100 . "AcDbEntity") (8 . "MASONRY") (62 . 7) (370 . 13) (100 . "AcDbLine") (10 10207.3897285068
5015.0834162896 0.0) (11 10184.7652941176 5015.0834162896 0.0))
((0 . "LINE") (100 . "AcDbEntity") (8 . "MASONRY") (62 . 7) (370 . 13) (100 . "AcDbLine") (10 10196.0775113122
3672.6993891403 0.0) (11 10184.7652941176 3672.6993891403 0.0))
((0 . "LINE") (100 . "AcDbEntity") (8 . "MASONRY") (62 . 7) (370 . 13) (100 . "AcDbLine") (10 10184.7652941176
1004.9024208145 0.0) (11 10199.8500904977 1004.9024208145 0.0))
((0 . "LINE") (100 . "AcDbEntity") (8 . "MASONRY") (62 . 7) (370 . 13) (100 . "AcDbLine") (10 10184.7652941176
1085.9728506787 0.0) (11 10184.7652941176 1074.6544230769 0.0))
((0 . "LINE") (100 . "AcDbEntity") (8 . "MASONRY") (62 . 7) (370 . 13) (100 . "AcDbLine") (10 10184.7652941176
1074.6544230769 0.0) (11 10184.7652941176 1004.9024208145 0.0))
((0 . "LINE") (100 . "AcDbEntity") (8 . "MASONRY") (62 . 7) (370 . 13) (100 . "AcDbLine") (10 10282.8054298643
248.8687782805 0.0) (11 10184.7652941176 248.8687782805 0.0))
((0 . "LINE") (100 . "AcDbEntity") (8 . "MASONRY") (62 . 7) (370 . 13) (100 . "AcDbLine") (10 10191.3659276018
2405.7317533937 0.0) (11 10388.3852036199 2405.7317533937 0.0))
((0 . "LINE") (100 . "AcDbEntity") (8 . "MASONRY") (62 . 7) (370 . 13) (100 . "AcDbLine") (10 10191.3659276018
2405.7317533937 0.0) (11 10191.3659276018 2334.0872511312 0.0))
((0 . "LINE") (100 . "AcDbEntity") (8 . "MASONRY") (62 . 7) (370 . 13) (100 . "AcDbLine") (10 10191.3659276018
2518.8539253394 0.0) (11 10191.3659276018 2405.7317533937 0.0))
((0 . "LINE") (100 . "AcDbEntity") (8 . "MASONRY") (62 . 7) (370 . 13) (100 . "AcDbLine") (10 10196.0775113122
5394.0420022624 0.0) (11 10188.5378733032 5394.0420022624 0.0))
((0 . "LINE") (100 . "AcDbEntity") (8 . "MASONRY") (62 . 7) (370 . 13) (100 . "AcDbLine") (10 10191.3659276018
2518.8539253394 0.0) (11 10363.8758597285 2518.8539253394 0.0))
((0 . "LINE") (100 . "AcDbEntity") (8 . "MASONRY") (62 . 7) (370 . 13) (100 . "AcDbLine") (10 10194.19260181
6025.6409049774 0.0) (11 10207.3897285068 6025.6409049774 0.0))
((0 . "LINE") (100 . "AcDbEntity") (8 . "MASONRY") (62 . 7) (370 . 13) (100 . "AcDbLine") (10 10194.19260181
6093.6754298643 0.0) (11 10194.19260181 6025.6409049774 0.0))
((0 . "LINE") (100 . "AcDbEntity") (8 . "MASONRY") (62 . 7) (370 . 13) (100 . "AcDbLine") (10 10192.3076923077
5493.9663574661 0.0) (11 10192.3076923077 5441.1764705882 0.0))
((0 . "LINE") (100 . "AcDbEntity") (8 . "MASONRY") (62 . 7) (370 . 13) (100 . "AcDbLine") (10 10388.3852036199
5441.1764705882 0.0) (11 10192.3076923077 5441.1764705882 0.0))
((0 . "LINE") (100 . "AcDbEntity") (8 . "MASONRY") (62 . 7) (370 . 13) (100 . "AcDbLine") (10 10192.3076923077
4251.5080656109 0.0) (11 10230.0141628959 4251.5080656109 0.0))
((0 . "LINE") (100 . "AcDbEntity") (8 . "MASONRY") (62 . 7) (370 . 13) (100 . "AcDbLine") (10 10377.0729864253
1342.3840271493 0.0) (11 10192.3076923077 1342.3840271493 0.0))
((0 . "LINE") (100 . "AcDbEntity") (8 . "MASONRY") (62 . 7) (370 . 13) (100 . "AcDbLine") (10 10191.3659276018
2334.0872511312 0.0) (11 10191.3659276018 2269.9851470588 0.0))
((0 . "LINE") (100 . "AcDbEntity") (8 . "MASONRY") (62 . 7) (370 . 13) (100 . "AcDbLine") (10 10392.1577828054
2334.0872511312 0.0) (11 10191.3659276018 2334.0872511312 0.0))
((0 . "LINE") (100 . "AcDbEntity") (8 . "MASONRY") (62 . 7) (370 . 13) (100 . "AcDbLine") (10 10373.3031674208
6093.6754298643 0.0) (11 10194.19260181 6093.6754298643 0.0))
((0 . "LINE") (100 . "AcDbEntity") (8 . "MASONRY") (62 . 7) (370 . 13) (100 . "AcDbLine") (10 10196.0775113122
3863.1221719457 0.0) (11 10211.1623076923 3863.1221719457 0.0))
((0 . "LINE") (100 . "AcDbEntity") (8 . "MASONRY") (62 . 7) (370 . 13) (100 . "AcDbLine") (10 10211.1623076923
3863.1221719457 0.0) (11 10226.2443438914 3863.1221719457 0.0))
((0 . "LINE") (100 . "AcDbEntity") (8 . "MASONRY") (62 . 7) (370 . 13) (100 . "AcDbLine") (10 10226.2443438914
3863.1221719457 0.0) (11 10263.9508144796 3863.1221719457 0.0))
((0 . "LINE") (100 . "AcDbEntity") (8 . "MASONRY") (62 . 7) (370 . 13) (100 . "AcDbLine") (10 10288.4615384615
2269.9851470588 0.0) (11 10191.3659276018 2269.9851470588 0.0))
((0 . "LINE") (100 . "AcDbEntity") (8 . "MASONRY") (62 . 7) (370 . 13) (100 . "AcDbLine") (10 10196.0775113122
1806.029581448 0.0) (11 10211.1623076923 1806.029581448 0.0))
((0 . "LINE") (100 . "AcDbEntity") (8 . "MASONRY") (62 . 7) (370 . 13) (100 . "AcDbLine") (10 10211.1623076923
1806.029581448 0.0) (11 10395.92760181 1806.029581448 0.0))
((0 . "LINE") (100 . "AcDbEntity") (8 . "MASONRY") (62 . 7) (370 . 13) (100 . "AcDbLine") (10 10197.963800905
1760.9360633484 0.0) (11 10197.963800905 1730.7692307692 0.0))
((0 . "LINE") (100 . "AcDbEntity") (8 . "MASONRY") (62 . 7) (370 . 13) (100 . "AcDbLine") (10 10199.8500904977
2096.5313800905 0.0) (11 10226.2443438914 2096.5313800905 0.0))
((0 . "LINE") (100 . "AcDbEntity") (8 . "MASONRY") (62 . 7) (370 . 13) (100 . "AcDbLine") (10 10199.8500904977
1855.2036199095 0.0) (11 10199.8500904977 1864.6309276018 0.0))
((0 . "LINE") (100 . "AcDbEntity") (8 . "MASONRY") (62 . 7) (370 . 13) (100 . "AcDbLine") (10 10309.1996832579
1864.6309276018 0.0) (11 10199.8500904977 1864.6309276018 0.0))
((0 . "LINE") (100 . "AcDbEntity") (8 . "MASONRY") (62 . 7) (370 . 13) (100 . "AcDbLine") (10 10197.963800905
1730.7692307692 0.0) (11 10230.0141628959 1730.7692307692 0.0))
((0 . "LINE") (100 . "AcDbEntity") (8 . "MASONRY") (62 . 7) (370 . 13) (100 . "AcDbLine") (10 10267.7233936652
6206.6363800905 0.0) (11 10203.6199095023 6206.6363800905 0.0))
((0 . "LINE") (100 . "AcDbEntity") (8 . "MASONRY") (62 . 7) (370 . 13) (100 . "AcDbLine") (10 10203.6199095023
6157.6170135747 0.0) (11 10203.6199095023 6206.6363800905 0.0))
((0 . "LINE") (100 . "AcDbEntity") (8 . "MASONRY") (62 . 7) (370 . 13) (100 . "AcDbLine") (10 10230.0141628959
3710.407239819 0.0) (11 10211.1623076923 3710.407239819 0.0))
((0 . "LINE") (100 . "AcDbEntity") (8 . "MASONRY") (62 . 7) (370 . 13) (100 . "AcDbLine") (10 10214.9321266968
2130.467341629 0.0) (11 10214.9321266968 2119.1551244344 0.0))
((0 . "LINE") (100 . "AcDbEntity") (8 . "MASONRY") (62 . 7) (370 . 13) (100 . "AcDbLine") (10 10218.7019457014
3333.3335633484 0.0) (11 10305.4298642534 3333.3335633484 0.0))
((0 . "LINE") (100 . "AcDbEntity") (8 . "MASONRY") (62 . 7) (370 . 13) (100 . "AcDbLine") (10 10305.4298642534
3333.3335633484 0.0) (11 10343.1363348416 3333.3335633484 0.0))
((0 . "LINE") (100 . "AcDbEntity") (8 . "MASONRY") (62 . 7) (370 . 13) (100 . "AcDbLine") (10 10218.7019457014
2865.761459276 0.0) (11 10326.1652488688 2865.761459276 0.0))
((0 . "LINE") (100 . "AcDbEntity") (8 . "MASONRY") (62 . 7) (370 . 13) (100 . "AcDbLine") (10 10326.1652488688
2865.761459276 0.0) (11 10326.1652488688 2880.8448755656 0.0))
((0 . "LINE") (100 . "AcDbEntity") (8 . "MASONRY") (62 . 7) (370 . 13) (100 . "AcDbLine") (10 10339.3665158371
1674.2081447964 0.0) (11 10218.7019457014 1674.2081447964 0.0))
((0 . "LINE") (100 . "AcDbEntity") (8 . "MASONRY") (62 . 7) (370 . 13) (100 . "AcDbLine") (10 10224.3594343891
3759.4273076923 0.0) (11 10224.3594343891 3766.9683257919 0.0))
((0 . "LINE") (100 . "AcDbEntity") (8 . "MASONRY") (62 . 7) (370 . 13) (100 . "AcDbLine") (10 10222.4745248869
3003.3163348416 0.0) (11 10238.8394004525 3003.3163348416 0.0))
((0 . "LINE") (100 . "AcDbEntity") (8 . "MASONRY") (62 . 7) (370 . 13) (100 . "AcDbLine") (10 10238.8394004525
3003.3163348416 0.0) (11 10238.8394004525 2944.946979638 0.0))
((0 . "LINE") (100 . "AcDbEntity") (8 . "MASONRY") (62 . 7) (370 . 13) (100 . "AcDbLine") (10 10226.2443438914
5642.3087104072 0.0) (11 10237.556561086 5642.3087104072 0.0))
((0 . "LINE") (100 . "AcDbEntity") (8 . "MASONRY") (62 . 7) (370 . 13) (100 . "AcDbLine") (10 10230.0141628959
3799.0193778281 0.0) (11 10245.098959276 3799.0193778281 0.0))
((0 . "LINE") (100 . "AcDbEntity") (8 . "MASONRY") (62 . 7) (370 . 13) (100 . "AcDbLine") (10 10245.098959276
3674.5849886878 0.0) (11 10230.0141628959 3674.5849886878 0.0))
((0 . "LINE") (100 . "AcDbEntity") (8 . "MASONRY") (62 . 7) (370 . 13) (100 . "AcDbLine") (10 10335.5966968326
1089.7440497738 0.0) (11 10233.7867420814 1089.7440497738 0.0))
((0 . "LINE") (100 . "AcDbEntity") (8 . "MASONRY") (62 . 7) (370 . 13) (100 . "AcDbLine") (10 10392.1577828054
1003.0175113122 0.0) (11 10233.7867420814 1003.0175113122 0.0))
((0 . "LINE") (100 . "AcDbEntity") (8 . "MASONRY") (62 . 7) (370 . 13) (100 . "AcDbLine") (10 10237.556561086
5642.3087104072 0.0) (11 10237.556561086 5602.1912217195 0.0))
((0 . "LINE") (100 . "AcDbEntity") (8 . "MASONRY") (62 . 7) (370 . 13) (100 . "AcDbLine") (10 10237.556561086
5642.3087104072 0.0) (11 10252.6385972851 5642.3087104072 0.0))
((0 . "LINE") (100 . "AcDbEntity") (8 . "MASONRY") (62 . 7) (370 . 13) (100 . "AcDbLine") (10 10252.6385972851
5642.3087104072 0.0) (11 10392.1577828054 5642.3087104072 0.0))
((0 . "LINE") (100 . "AcDbEntity") (8 . "MASONRY") (62 . 7) (370 . 13) (100 . "AcDbLine") (10 10237.556561086
5602.1912217195 0.0) (11 10237.556561086 5546.7576244344 0.0))
((0 . "LINE") (100 . "AcDbEntity") (8 . "MASONRY") (62 . 7) (370 . 13) (100 . "AcDbLine") (10 10237.556561086
5222.4731447964 0.0) (11 10256.4111764706 5222.4731447964 0.0))
((0 . "LINE") (100 . "AcDbEntity") (8 . "MASONRY") (62 . 7) (370 . 13) (100 . "AcDbLine") (10 10237.556561086
3631.221719457 0.0) (11 10273.3781221719 3631.221719457 0.0))
((0 . "LINE") (100 . "AcDbEntity") (8 . "MASONRY") (62 . 7) (370 . 13) (100 . "AcDbLine") (10 10248.875678733
3061.8403506787 0.0) (11 10248.875678733 3035.5220475113 0.0))
((0 . "LINE") (100 . "AcDbEntity") (8 . "MASONRY") (62 . 7) (370 . 13) (100 . "AcDbLine") (10 10248.875678733
3035.5220475113 0.0) (11 10392.1577828054 3035.5220475113 0.0))
((0 . "LINE") (100 . "AcDbEntity") (8 . "MASONRY") (62 . 7) (370 . 13) (100 . "AcDbLine") (10 10248.875678733
3061.8403506787 0.0) (11 10248.875678733 3099.019321267 0.0))
((0 . "LINE") (100 . "AcDbEntity") (8 . "MASONRY") (62 . 7) (370 . 13) (100 . "AcDbLine") (10 10248.875678733
3099.019321267 0.0) (11 10388.3852036199 3099.019321267 0.0))
((0 . "LINE") (100 . "AcDbEntity") (8 . "MASONRY") (62 . 7) (370 . 13) (100 . "AcDbLine") (10 10241.3263800905
6025.4928054299 0.0) (11 10365.7607692308 6025.4928054299 0.0))
((0 . "LINE") (100 . "AcDbEntity") (8 . "MASONRY") (62 . 7) (370 . 13) (100 . "AcDbLine") (10 10365.7607692308
6025.4928054299 0.0) (11 10383.9387556561 6025.4928054299 0.0))
((0 . "LINE") (100 . "AcDbEntity") (8 . "MASONRY") (62 . 7) (370 . 13) (100 . "AcDbLine") (10 10383.9387556561
6025.4928054299 0.0) (11 10383.9387556561 5995.4751131222 0.0))
((0 . "LINE") (100 . "AcDbEntity") (8 . "MASONRY") (62 . 7) (370 . 13) (100 . "AcDbLine") (10 10331.8241176471
5546.7576244344 0.0) (11 10237.556561086 5546.7576244344 0.0))
((0 . "LINE") (100 . "AcDbEntity") (8 . "MASONRY") (62 . 7) (370 . 13) (100 . "AcDbLine") (10 10241.3263800905
5011.3122171946 0.0) (11 10248.8687782805 5011.3122171946 0.0))
((0 . "LINE") (100 . "AcDbEntity") (8 . "MASONRY") (62 . 7) (370 . 13) (100 . "AcDbLine") (10 10243.2126696833
4920.814479638 0.0) (11 10243.2126696833 4892.5339366516 0.0))
((0 . "LINE") (100 . "AcDbEntity") (8 . "MASONRY") (62 . 7) (370 . 13) (100 . "AcDbLine") (10 10241.3263800905
4690.7989366516 0.0) (11 10241.3263800905 4668.1745022624 0.0))
((0 . "LINE") (100 . "AcDbEntity") (8 . "MASONRY") (62 . 7) (370 . 13) (100 . "AcDbLine") (10 10392.1577828054
4634.2378506787 0.0) (11 10241.3263800905 4634.2378506787 0.0))
((0 . "LINE") (100 . "AcDbEntity") (8 . "MASONRY") (62 . 7) (370 . 13) (100 . "AcDbLine") (10 10241.3263800905
4634.2378506787 0.0) (11 10241.3263800905 4615.3846153846 0.0))
((0 . "LINE") (100 . "AcDbEntity") (8 . "MASONRY") (62 . 7) (370 . 13) (100 . "AcDbLine") (10 10241.3263800905
3506.6326696833 0.0) (11 10241.3263800905 3472.850678733 0.0))
((0 . "LINE") (100 . "AcDbEntity") (8 . "MASONRY") (62 . 7) (370 . 13) (100 . "AcDbLine") (10 10263.9508144796
3506.6326696833 0.0) (11 10241.3263800905 3506.6326696833 0.0))
((0 . "LINE") (100 . "AcDbEntity") (8 . "MASONRY") (62 . 7) (370 . 13) (100 . "AcDbLine") (10 10388.3852036199
3472.850678733 0.0) (11 10241.3263800905 3472.850678733 0.0))
((0 . "LINE") (100 . "AcDbEntity") (8 . "MASONRY") (62 . 7) (370 . 13) (100 . "AcDbLine") (10 10392.1577828054
2944.946979638 0.0) (11 10238.8394004525 2944.946979638 0.0))
((0 . "LINE") (100 . "AcDbEntity") (8 . "MASONRY") (62 . 7) (370 . 13) (100 . "AcDbLine") (10 10245.0975791855
2771.4932126697 0.0) (11 10245.0975791855 2726.2443438914 0.0))
((0 . "LINE") (100 . "AcDbEntity") (8 . "MASONRY") (62 . 7) (370 . 13) (100 . "AcDbLine") (10 10241.3263800905
1730.7692307692 0.0) (11 10346.9089140271 1730.7692307692 0.0))
((0 . "LINE") (100 . "AcDbEntity") (8 . "MASONRY") (62 . 7) (370 . 13) (100 . "AcDbLine") (10 10346.9089140271
1730.7692307692 0.0) (11 10392.1577828054 1730.7692307692 0.0))
((0 . "LINE") (100 . "AcDbEntity") (8 . "MASONRY") (62 . 7) (370 . 13) (100 . "AcDbLine") (10 10388.3852036199
424.2854751131 0.0) (11 10245.1010294118 424.2854751131 0.0))
((0 . "LINE") (100 . "AcDbEntity") (8 . "MASONRY") (62 . 7) (370 . 13) (100 . "AcDbLine") (10 10245.1010294118
424.2854751131 0.0) (11 10245.1010294118 441.1764705882 0.0))
((0 . "LINE") (100 . "AcDbEntity") (8 . "MASONRY") (62 . 7) (370 . 13) (100 . "AcDbLine") (10 10316.742081448
75.4157013575 0.0) (11 10241.3263800905 75.4157013575 0.0))
((0 . "LINE") (100 . "AcDbEntity") (8 . "MASONRY") (62 . 7) (370 . 13) (100 . "AcDbLine") (10 10250.7550678733
5908.7482352941 0.0) (11 10250.7550678733 5946.4553846154 0.0))
((0 . "LINE") (100 . "AcDbEntity") (8 . "MASONRY") (62 . 7) (370 . 13) (100 . "AcDbLine") (10 10250.7550678733
5946.4553846154 0.0) (11 10354.4485520362 5946.4553846154 0.0))
((0 . "LINE") (100 . "AcDbEntity") (8 . "MASONRY") (62 . 7) (370 . 13) (100 . "AcDbLine") (10 10243.2126696833
4892.5339366516 0.0) (11 10388.3852036199 4892.5339366516 0.0))
((0 . "LINE") (100 . "AcDbEntity") (8 . "MASONRY") (62 . 7) (370 . 13) (100 . "AcDbLine") (10 10246.9838687783
4377.8280542986 0.0) (11 10246.9838687783 4402.3380882353 0.0))
((0 . "LINE") (100 . "AcDbEntity") (8 . "MASONRY") (62 . 7) (370 . 13) (100 . "AcDbLine") (10 10286.5752488688
952.1111538462 0.0) (11 10245.098959276 952.1111538462 0.0))
((0 . "LINE") (100 . "AcDbEntity") (8 . "MASONRY") (62 . 7) (370 . 13) (100 . "AcDbLine") (10 10245.098959276
855.9586877828 0.0) (11 10260.1809954751 855.9586877828 0.0))
((0 . "LINE") (100 . "AcDbEntity") (8 . "MASONRY") (62 . 7) (370 . 13) (100 . "AcDbLine") (10 10248.8687782805
4973.6043665158 0.0) (11 10248.8687782805 5011.3122171946 0.0))
((0 . "LINE") (100 . "AcDbEntity") (8 . "MASONRY") (62 . 7) (370 . 13) (100 . "AcDbLine") (10 10279.0356108597
5011.3122171946 0.0) (11 10248.8687782805 5011.3122171946 0.0))
((0 . "LINE") (100 . "AcDbEntity") (8 . "MASONRY") (62 . 7) (370 . 13) (100 . "AcDbLine") (10 10248.8687782805
4973.6043665158 0.0) (11 10388.3852036199 4973.6043665158 0.0))
((0 . "LINE") (100 . "AcDbEntity") (8 . "MASONRY") (62 . 7) (370 . 13) (100 . "AcDbLine") (10 10358.2211312217
4402.3380882353 0.0) (11 10246.9838687783 4402.3380882353 0.0))
((0 . "LINE") (100 . "AcDbEntity") (8 . "MASONRY") (62 . 7) (370 . 13) (100 . "AcDbLine") (10 10250.7536877828
3152.3380882353 0.0) (11 10250.7536877828 3186.274739819 0.0))
((0 . "LINE") (100 . "AcDbEntity") (8 . "MASONRY") (62 . 7) (370 . 13) (100 . "AcDbLine") (10 10245.0975791855
2771.4932126697 0.0) (11 10388.3852036199 2771.4932126697 0.0))
((0 . "LINE") (100 . "AcDbEntity") (8 . "MASONRY") (62 . 7) (370 . 13) (100 . "AcDbLine") (10 10248.8687782805
2692.3076923077 0.0) (11 10388.3852036199 2692.3076923077 0.0))
((0 . "LINE") (100 . "AcDbEntity") (8 . "MASONRY") (62 . 7) (370 . 13) (100 . "AcDbLine") (10 10388.3852036199
3186.274739819 0.0) (11 10250.7536877828 3186.274739819 0.0))
((0 . "LINE") (100 . "AcDbEntity") (8 . "MASONRY") (62 . 7) (370 . 13) (100 . "AcDbLine") (10 10252.6385972851
2654.6005316742 0.0) (11 10252.6385972851 2628.20489819 0.0))
((0 . "LINE") (100 . "AcDbEntity") (8 . "MASONRY") (62 . 7) (370 . 13) (100 . "AcDbLine") (10 10252.6385972851
2628.20489819 0.0) (11 10358.2211312217 2628.20489819 0.0))
((0 . "LINE") (100 . "AcDbEntity") (8 . "MASONRY") (62 . 7) (370 . 13) (100 . "AcDbLine") (10 10260.1809954751
904.9773755656 0.0) (11 10252.6385972851 904.9773755656 0.0))
((0 . "LINE") (100 . "AcDbEntity") (8 . "MASONRY") (62 . 7) (370 . 13) (100 . "AcDbLine") (10 10252.6385972851
816.3645475113 0.0) (11 10365.7607692308 816.3645475113 0.0))
((0 . "LINE") (100 . "AcDbEntity") (8 . "MASONRY") (62 . 7) (370 . 13) (100 . "AcDbLine") (10 10290.3478280543
6308.3690158371 0.0) (11 10267.7233936652 6308.3690158371 0.0))
((0 . "LINE") (100 . "AcDbEntity") (8 . "MASONRY") (62 . 7) (370 . 13) (100 . "AcDbLine") (10 10384.6153846154
3863.1221719457 0.0) (11 10263.9508144796 3863.1221719457 0.0))
((0 . "LINE") (100 . "AcDbEntity") (8 . "MASONRY") (62 . 7) (370 . 13) (100 . "AcDbLine") (10 10267.7233936652
6304.6758371041 0.0) (11 10267.7233936652 6206.6363800905 0.0))
((0 . "LINE") (100 . "AcDbEntity") (8 . "MASONRY") (62 . 7) (370 . 13) (100 . "AcDbLine") (10 10267.7233936652
6304.6758371041 0.0) (11 10290.3478280543 6304.6758371041 0.0))
((0 . "LINE") (100 . "AcDbEntity") (8 . "MASONRY") (62 . 7) (370 . 13) (100 . "AcDbLine") (10 10388.3852036199
6206.6363800905 0.0) (11 10267.7233936652 6206.6363800905 0.0))
((0 . "LINE") (100 . "AcDbEntity") (8 . "MASONRY") (62 . 7) (370 . 13) (100 . "AcDbLine") (10 10273.3781221719
3631.221719457 0.0) (11 10273.3781221719 3593.5145588235 0.0))
((0 . "LINE") (100 . "AcDbEntity") (8 . "MASONRY") (62 . 7) (370 . 13) (100 . "AcDbLine") (10 10328.0542986425
3678.3561877828 0.0) (11 10275.2630316742 3678.3561877828 0.0))
((0 . "LINE") (100 . "AcDbEntity") (8 . "MASONRY") (62 . 7) (370 . 13) (100 . "AcDbLine") (10 10392.1577828054
3631.221719457 0.0) (11 10273.3781221719 3631.221719457 0.0))
((0 . "LINE") (100 . "AcDbEntity") (8 . "MASONRY") (62 . 7) (370 . 13) (100 . "AcDbLine") (10 10275.2630316742
3570.9674547511 0.0) (11 10354.4464819005 3570.9674547511 0.0))
((0 . "LINE") (100 . "AcDbEntity") (8 . "MASONRY") (62 . 7) (370 . 13) (100 . "AcDbLine") (10 10354.4464819005
3570.9674547511 0.0) (11 10354.4464819005 3582.202341629 0.0))
((0 . "LINE") (100 . "AcDbEntity") (8 . "MASONRY") (62 . 7) (370 . 13) (100 . "AcDbLine") (10 10275.2630316742
3527.5268552036 0.0) (11 10354.4485520362 3527.5268552036 0.0))
((0 . "LINE") (100 . "AcDbEntity") (8 . "MASONRY") (62 . 7) (370 . 13) (100 . "AcDbLine") (10 10280.920520362
4170.4369457014 0.0) (11 10280.920520362 4144.0426923077 0.0))
((0 . "LINE") (100 . "AcDbEntity") (8 . "MASONRY") (62 . 7) (370 . 13) (100 . "AcDbLine") (10 10369.5333484163
3791.4783597285 0.0) (11 10279.0356108597 3791.4783597285 0.0))
((0 . "LINE") (100 . "AcDbEntity") (8 . "MASONRY") (62 . 7) (370 . 13) (100 . "AcDbLine") (10 10280.920520362
4144.0426923077 0.0) (11 10388.3852036199 4144.0426923077 0.0))
((0 . "LINE") (100 . "AcDbEntity") (8 . "MASONRY") (62 . 7) (370 . 13) (100 . "AcDbLine") (10 10388.3852036199
6391.4027149321 0.0) (11 10286.5752488688 6391.4027149321 0.0))
((0 . "LINE") (100 . "AcDbEntity") (8 . "MASONRY") (62 . 7) (370 . 13) (100 . "AcDbLine") (10 10286.5752488688
6361.2369230769 0.0) (11 10286.5752488688 6391.4027149321 0.0))
((0 . "LINE") (100 . "AcDbEntity") (8 . "MASONRY") (62 . 7) (370 . 13) (100 . "AcDbLine") (10 10290.3478280543
6308.3690158371 0.0) (11 10290.3478280543 6327.3002714932 0.0))
((0 . "LINE") (100 . "AcDbEntity") (8 . "MASONRY") (62 . 7) (370 . 13) (100 . "AcDbLine") (10 10286.5752488688
4253.3936651584 0.0) (11 10358.2211312217 4253.3936651584 0.0))
((0 . "LINE") (100 . "AcDbEntity") (8 . "MASONRY") (62 . 7) (370 . 13) (100 . "AcDbLine") (10 10288.4615384615
2243.5895135747 0.0) (11 10288.4615384615 2269.9851470588 0.0))
((0 . "LINE") (100 . "AcDbEntity") (8 . "MASONRY") (62 . 7) (370 . 13) (100 . "AcDbLine") (10 10380.8455656109
1185.2958257919 0.0) (11 10290.34989819 1185.2958257919 0.0))
((0 . "LINE") (100 . "AcDbEntity") (8 . "MASONRY") (62 . 7) (370 . 13) (100 . "AcDbLine") (10 10350.6787330317
1219.2352488688 0.0) (11 10290.34989819 1219.2352488688 0.0))
((0 . "LINE") (100 . "AcDbEntity") (8 . "MASONRY") (62 . 7) (370 . 13) (100 . "AcDbLine") (10 10290.34989819
1219.2352488688 0.0) (11 10290.34989819 1185.2958257919 0.0))
((0 . "LINE") (100 . "AcDbEntity") (8 . "MASONRY") (62 . 7) (370 . 13) (100 . "AcDbLine") (10 10388.3852036199
6304.6758371041 0.0) (11 10290.3478280543 6304.6758371041 0.0))
((0 . "LINE") (100 . "AcDbEntity") (8 . "MASONRY") (62 . 7) (370 . 13) (100 . "AcDbLine") (10 10288.4615384615
2269.9851470588 0.0) (11 10388.3852036199 2269.9851470588 0.0))
((0 . "LINE") (100 . "AcDbEntity") (8 . "MASONRY") (62 . 7) (370 . 13) (100 . "AcDbLine") (10 10388.3852036199
4599.7730090498 0.0) (11 10311.0859728507 4599.7730090498 0.0))
((0 . "LINE") (100 . "AcDbEntity") (8 . "MASONRY") (62 . 7) (370 . 13) (100 . "AcDbLine") (10 10311.0859728507
4599.7730090498 0.0) (11 10311.0859728507 4562.5947285068 0.0))
((0 . "LINE") (100 . "AcDbEntity") (8 . "MASONRY") (62 . 7) (370 . 13) (100 . "AcDbLine") (10 10312.9708823529
5041.4776696833 0.0) (11 10312.9708823529 5015.0834162896 0.0))
((0 . "LINE") (100 . "AcDbEntity") (8 . "MASONRY") (62 . 7) (370 . 13) (100 . "AcDbLine") (10 10313.0482126697
1957.0135746606 0.0) (11 10313.0482126697 1984.6920475113 0.0))
((0 . "LINE") (100 . "AcDbEntity") (8 . "MASONRY") (62 . 7) (370 . 13) (100 . "AcDbLine") (10 10313.0482126697
1984.6920475113 0.0) (11 10392.1577828054 1984.6920475113 0.0))
((0 . "LINE") (100 . "AcDbEntity") (8 . "MASONRY") (62 . 7) (370 . 13) (100 . "AcDbLine") (10 10309.1996832579
1864.6309276018 0.0) (11 10309.1996832579 1915.5352149321 0.0))
((0 . "LINE") (100 . "AcDbEntity") (8 . "MASONRY") (62 . 7) (370 . 13) (100 . "AcDbLine") (10 10309.1996832579
1864.6309276018 0.0) (11 10392.1577828054 1864.6309276018 0.0))
((0 . "LINE") (100 . "AcDbEntity") (8 . "MASONRY") (62 . 7) (370 . 13) (100 . "AcDbLine") (10 10388.3852036199
950.2262443439 0.0) (11 10309.1996832579 950.2262443439 0.0))
((0 . "LINE") (100 . "AcDbEntity") (8 . "MASONRY") (62 . 7) (370 . 13) (100 . "AcDbLine") (10 10395.92760181
854.07239819 0.0) (11 10309.1996832579 854.07239819 0.0))
((0 . "LINE") (100 . "AcDbEntity") (8 . "MASONRY") (62 . 7) (370 . 13) (100 . "AcDbLine") (10 10318.6269909502
5064.1021040724 0.0) (11 10318.6269909502 5086.7265384615 0.0))
((0 . "LINE") (100 . "AcDbEntity") (8 . "MASONRY") (62 . 7) (370 . 13) (100 . "AcDbLine") (10 10316.742081448
75.4157013575 0.0) (11 10316.742081448 177.2256561086 0.0))
((0 . "LINE") (100 . "AcDbEntity") (8 . "MASONRY") (62 . 7) (370 . 13) (100 . "AcDbLine") (10 10392.1577828054
177.2256561086 0.0) (11 10316.742081448 177.2256561086 0.0))
((0 . "LINE") (100 . "AcDbEntity") (8 . "MASONRY") (62 . 7) (370 . 13) (100 . "AcDbLine") (10 10316.742081448
75.4157013575 0.0) (11 10384.6153846154 75.4157013575 0.0))
((0 . "LINE") (100 . "AcDbEntity") (8 . "MASONRY") (62 . 7) (370 . 13) (100 . "AcDbLine") (10 10384.6153846154
4074.2837895928 0.0) (11 10320.5119004525 4074.2837895928 0.0))
((0 . "LINE") (100 . "AcDbEntity") (8 . "MASONRY") (62 . 7) (370 . 13) (100 . "AcDbLine") (10 10322.3981900452
614.6295475113 0.0) (11 10322.3981900452 592.0051131222 0.0))
((0 . "LINE") (100 . "AcDbEntity") (8 . "MASONRY") (62 . 7) (370 . 13) (100 . "AcDbLine") (10 10318.7788914027
3989.4414705882 0.0) (11 10392.1577828054 3989.4414705882 0.0))
((0 . "LINE") (100 . "AcDbEntity") (8 . "MASONRY") (62 . 7) (370 . 13) (100 . "AcDbLine") (10 10324.284479638
671.1906334842 0.0) (11 10324.284479638 678.7330316742 0.0))
((0 . "LINE") (100 . "AcDbEntity") (8 . "MASONRY") (62 . 7) (370 . 13) (100 . "AcDbLine") (10 10324.284479638
565.6108597285 0.0) (11 10324.284479638 537.3303167421 0.0))
((0 . "LINE") (100 . "AcDbEntity") (8 . "MASONRY") (62 . 7) (370 . 13) (100 . "AcDbLine") (10 10388.3852036199
537.3303167421 0.0) (11 10324.284479638 537.3303167421 0.0))
((0 . "LINE") (100 . "AcDbEntity") (8 . "MASONRY") (62 . 7) (370 . 13) (100 . "AcDbLine") (10 10358.2211312217
4483.4092081448 0.0) (11 10328.0542986425 4483.4092081448 0.0))
((0 . "LINE") (100 . "AcDbEntity") (8 . "MASONRY") (62 . 7) (370 . 13) (100 . "AcDbLine") (10 10329.9392081448
2907.2398190045 0.0) (11 10329.9392081448 2892.1570927602 0.0))
((0 . "LINE") (100 . "AcDbEntity") (8 . "MASONRY") (62 . 7) (370 . 13) (100 . "AcDbLine") (10 10331.8241176471
2021.1163687783 0.0) (11 10331.8241176471 2045.7037330317 0.0))
((0 . "LINE") (100 . "AcDbEntity") (8 . "MASONRY") (62 . 7) (370 . 13) (100 . "AcDbLine") (10 10331.8241176471
2045.7037330317 0.0) (11 10331.8241176471 2055.053020362 0.0))
((0 . "LINE") (100 . "AcDbEntity") (8 . "MASONRY") (62 . 7) (370 . 13) (100 . "AcDbLine") (10 10350.6787330317
2055.053020362 0.0) (11 10331.8241176471 2055.053020362 0.0))
((0 . "LINE") (100 . "AcDbEntity") (8 . "MASONRY") (62 . 7) (370 . 13) (100 . "AcDbLine") (10 10331.8241176471
2055.053020362 0.0) (11 10331.8241176471 2147.3590271493 0.0))
((0 . "LINE") (100 . "AcDbEntity") (8 . "MASONRY") (62 . 7) (370 . 13) (100 . "AcDbLine") (10 10331.8241176471
2147.3590271493 0.0) (11 10388.3852036199 2147.3590271493 0.0))
((0 . "LINE") (100 . "AcDbEntity") (8 . "MASONRY") (62 . 7) (370 . 13) (100 . "AcDbLine") (10 10343.1363348416
5403.4686199095 0.0) (11 10335.5966968326 5403.4686199095 0.0))
((0 . "LINE") (100 . "AcDbEntity") (8 . "MASONRY") (62 . 7) (370 . 13) (100 . "AcDbLine") (10 10335.5966968326
2835.5960067873 0.0) (11 10335.5966968326 2824.2837895928 0.0))
((0 . "LINE") (100 . "AcDbEntity") (8 . "MASONRY") (62 . 7) (370 . 13) (100 . "AcDbLine") (10 10341.2583257919
3291.8552036199 0.0) (11 10341.2583257919 3275.4889479638 0.0))
((0 . "LINE") (100 . "AcDbEntity") (8 . "MASONRY") (62 . 7) (370 . 13) (100 . "AcDbLine") (10 10341.2583257919
3275.4889479638 0.0) (11 10388.3852036199 3275.4889479638 0.0))
((0 . "LINE") (100 . "AcDbEntity") (8 . "MASONRY") (62 . 7) (370 . 13) (100 . "AcDbLine") (10 10345.0226244344
5727.752760181 0.0) (11 10392.1577828054 5727.752760181 0.0))
((0 . "LINE") (100 . "AcDbEntity") (8 . "MASONRY") (62 . 7) (370 . 13) (100 . "AcDbLine") (10 10345.0226244344
5746.6063348416 0.0) (11 10345.0226244344 5727.752760181 0.0))
((0 . "LINE") (100 . "AcDbEntity") (8 . "MASONRY") (62 . 7) (370 . 13) (100 . "AcDbLine") (10 10348.7924434389
1595.0226244344 0.0) (11 10348.7924434389 1561.0859728507 0.0))
((0 . "LINE") (100 . "AcDbEntity") (8 . "MASONRY") (62 . 7) (370 . 13) (100 . "AcDbLine") (10 10343.1363348416
1478.1306334842 0.0) (11 10343.1363348416 1440.4214027149 0.0))
((0 . "LINE") (100 . "AcDbEntity") (8 . "MASONRY") (62 . 7) (370 . 13) (100 . "AcDbLine") (10 10388.3852036199
1440.4214027149 0.0) (11 10343.1363348416 1440.4214027149 0.0))
((0 . "LINE") (100 . "AcDbEntity") (8 . "MASONRY") (62 . 7) (370 . 13) (100 . "AcDbLine") (10 10354.4485520362
245.098959276 0.0) (11 10354.4485520362 260.1809954751 0.0))
((0 . "LINE") (100 . "AcDbEntity") (8 . "MASONRY") (62 . 7) (370 . 13) (100 . "AcDbLine") (10 10354.4485520362
260.1809954751 0.0) (11 10354.4485520362 354.4485520362 0.0))
((0 . "LINE") (100 . "AcDbEntity") (8 . "MASONRY") (62 . 7) (370 . 13) (100 . "AcDbLine") (10 10392.1577828054
4515.460260181 0.0) (11 10350.6787330317 4515.460260181 0.0))
((0 . "LINE") (100 . "AcDbEntity") (8 . "MASONRY") (62 . 7) (370 . 13) (100 . "AcDbLine") (10 10392.1577828054
5135.5919457014 0.0) (11 10354.4485520362 5135.5919457014 0.0))
((0 . "LINE") (100 . "AcDbEntity") (8 . "MASONRY") (62 . 7) (370 . 13) (100 . "AcDbLine") (10 10354.4485520362
3674.5849886878 0.0) (11 10380.8455656109 3674.5849886878 0.0))
((0 . "LINE") (100 . "AcDbEntity") (8 . "MASONRY") (62 . 7) (370 . 13) (100 . "AcDbLine") (10 10395.92760181
1595.0226244344 0.0) (11 10348.7924434389 1595.0226244344 0.0))
((0 . "LINE") (100 . "AcDbEntity") (8 . "MASONRY") (62 . 7) (370 . 13) (100 . "AcDbLine") (10 10388.3852036199
354.4485520362 0.0) (11 10354.4485520362 354.4485520362 0.0))
((0 . "LINE") (100 . "AcDbEntity") (8 . "MASONRY") (62 . 7) (370 . 13) (100 . "AcDbLine") (10 10388.3852036199
5190.4220927602 0.0) (11 10358.2211312217 5190.4220927602 0.0))
((0 . "LINE") (100 . "AcDbEntity") (8 . "MASONRY") (62 . 7) (370 . 13) (100 . "AcDbLine") (10 10358.2211312217
4402.3380882353 0.0) (11 10358.2211312217 4434.3891402715 0.0))
((0 . "LINE") (100 . "AcDbEntity") (8 . "MASONRY") (62 . 7) (370 . 13) (100 . "AcDbLine") (10 10358.2211312217
4402.3380882353 0.0) (11 10384.6153846154 4402.3380882353 0.0))
((0 . "LINE") (100 . "AcDbEntity") (8 . "MASONRY") (62 . 7) (370 . 13) (100 . "AcDbLine") (10 10377.0729864253
1093.5152488688 0.0) (11 10358.2211312217 1093.5152488688 0.0))
((0 . "LINE") (100 . "AcDbEntity") (8 . "MASONRY") (62 . 7) (370 . 13) (100 . "AcDbLine") (10 10392.1577828054
2518.8539253394 0.0) (11 10363.8758597285 2518.8539253394 0.0))
((0 . "LINE") (100 . "AcDbEntity") (8 . "MASONRY") (62 . 7) (370 . 13) (100 . "AcDbLine") (10 10363.8758597285
2575.4150113122 0.0) (11 10363.8758597285 2518.8539253394 0.0))
((0 . "LINE") (100 . "AcDbEntity") (8 . "MASONRY") (62 . 7) (370 . 13) (100 . "AcDbLine") (10 10378.9592760181
5542.9864253394 0.0) (11 10365.7607692308 5542.9864253394 0.0))
((0 . "LINE") (100 . "AcDbEntity") (8 . "MASONRY") (62 . 7) (370 . 13) (100 . "AcDbLine") (10 10384.6153846154
4800.1505995475 0.0) (11 10373.3031674208 4800.1505995475 0.0))
((0 . "LINE") (100 . "AcDbEntity") (8 . "MASONRY") (62 . 7) (370 . 13) (100 . "AcDbLine") (10 10392.1577828054
2056.9386199095 0.0) (11 10373.3031674208 2056.9386199095 0.0))
((0 . "LINE") (100 . "AcDbEntity") (8 . "MASONRY") (62 . 7) (370 . 13) (100 . "AcDbLine") (10 10392.1577828054
5944.5701357466 0.0) (11 10377.0729864253 5944.5701357466 0.0))
((0 . "LINE") (100 . "AcDbEntity") (8 . "MASONRY") (62 . 7) (370 . 13) (100 . "AcDbLine") (10 10378.9592760181
5542.9864253394 0.0) (11 10378.9592760181 5512.8209728507 0.0))
((0 . "LINE") (100 . "AcDbEntity") (8 . "MASONRY") (62 . 7) (370 . 13) (100 . "AcDbLine") (10 10384.6153846154
5542.9864253394 0.0) (11 10378.9592760181 5542.9864253394 0.0))
((0 . "LINE") (100 . "AcDbEntity") (8 . "MASONRY") (62 . 7) (370 . 13) (100 . "AcDbLine") (10 10377.0729864253
5488.3102488688 0.0) (11 10395.92760181 5488.3102488688 0.0))
((0 . "LINE") (100 . "AcDbEntity") (8 . "MASONRY") (62 . 7) (370 . 13) (100 . "AcDbLine") (10 10377.0729864253
4864.2533936652 0.0) (11 10377.0729864253 4845.400158371 0.0))
((0 . "LINE") (100 . "AcDbEntity") (8 . "MASONRY") (62 . 7) (370 . 13) (100 . "AcDbLine") (10 10377.0729864253
3930.9954751131 0.0) (11 10388.3852036199 3930.9954751131 0.0))
((0 . "LINE") (100 . "AcDbEntity") (8 . "MASONRY") (62 . 7) (370 . 13) (100 . "AcDbLine") (10 10377.0729864253
1342.3840271493 0.0) (11 10377.0729864253 1312.2171945701 0.0))
((0 . "LINE") (100 . "AcDbEntity") (8 . "MASONRY") (62 . 7) (370 . 13) (100 . "AcDbLine") (10 10377.0729864253
1342.3840271493 0.0) (11 10392.1577828054 1342.3840271493 0.0))
((0 . "LINE") (100 . "AcDbEntity") (8 . "MASONRY") (62 . 7) (370 . 13) (100 . "AcDbLine") (10 10377.0729864253
1093.5152488688 0.0) (11 10377.0729864253 1157.6159728507 0.0))
((0 . "LINE") (100 . "AcDbEntity") (8 . "MASONRY") (62 . 7) (370 . 13) (100 . "AcDbLine") (10 10392.1577828054
1093.5152488688 0.0) (11 10377.0729864253 1093.5152488688 0.0))
((0 . "LINE") (100 . "AcDbEntity") (8 . "MASONRY") (62 . 7) (370 . 13) (100 . "AcDbLine") (10 10380.8455656109
814.479638009 0.0) (11 10395.92760181 814.479638009 0.0))
((0 . "LINE") (100 . "AcDbEntity") (8 . "MASONRY") (62 . 7) (370 . 13) (100 . "AcDbLine") (10 10392.1564027149
5920.0604524887 0.0) (11 10392.1564027149 5874.8115837104 0.0))
((0 . "LINE") (100 . "AcDbEntity") (8 . "MASONRY") (62 . 7) (370 . 13) (100 . "AcDbLine") (10 10395.92760181
4766.214638009 0.0) (11 10395.92760181 4777.5268552036 0.0))
((0 . "LINE") (100 . "AcDbEntity") (8 . "MASONRY") (62 . 7) (370 . 13) (100 . "AcDbLine") (10 12051.2825113122
2820.5125904977 0.0) (11 12051.2825113122 2707.390418552 0.0))
((0 . "LINE") (100 . "AcDbEntity") (8 . "MASONRY") (62 . 7) (370 . 13) (100 . "AcDbLine") (10 12051.2825113122
2820.5125904977 0.0) (11 12051.2825113122 3580.3167420814 0.0))
((0 . "LINE") (100 . "AcDbEntity") (8 . "MASONRY") (62 . 7) (370 . 13) (100 . "AcDbLine") (10 12051.2825113122
2707.390418552 0.0) (11 12051.2825113122 2096.5306900452 0.0))
((0 . "LINE") (100 . "AcDbEntity") (8 . "MASONRY") (62 . 7) (370 . 13) (100 . "AcDbLine") (10 12051.2825113122
220.5882352941 0.0) (11 12051.2825113122 369.5333484163 0.0))
((0 . "LINE") (100 . "AcDbEntity") (8 . "MASONRY") (62 . 7) (370 . 13) (100 . "AcDbLine") (10 12051.2825113122
369.5333484163 0.0) (11 12051.2825113122 652.3387782805 0.0))
((0 . "LINE") (100 . "AcDbEntity") (8 . "MASONRY") (62 . 7) (370 . 13) (100 . "AcDbLine") (10 12051.2825113122
652.3387782805 0.0) (11 12051.2825113122 2096.5306900452 0.0))
((0 . "LINE") (100 . "AcDbEntity") (8 . "MASONRY") (62 . 7) (370 . 13) (100 . "AcDbLine") (10 12104.07239819
3476.6211877828 0.0) (11 12341.628959276 3476.6211877828 0.0))
((0 . "LINE") (100 . "AcDbEntity") (8 . "MASONRY") (62 . 7) (370 . 13) (100 . "AcDbLine") (10 12341.628959276
3476.6211877828 0.0) (11 13118.4007466063 3476.6211877828 0.0))
((0 . "LINE") (100 . "AcDbEntity") (8 . "MASONRY") (62 . 7) (370 . 13) (100 . "AcDbLine") (10 12122.9256334842
2034.3141855204 0.0) (11 12104.07239819 2034.3141855204 0.0))
((0 . "LINE") (100 . "AcDbEntity") (8 . "MASONRY") (62 . 7) (370 . 13) (100 . "AcDbLine") (10 12179.486719457
1972.096300905 0.0) (11 12104.07239819 1972.096300905 0.0))
((0 . "LINE") (100 . "AcDbEntity") (8 . "MASONRY") (62 . 7) (370 . 13) (100 . "AcDbLine") (10 12130.4680316742
1344.2689366516 0.0) (11 12104.07239819 1344.2689366516 0.0))
((0 . "LINE") (100 . "AcDbEntity") (8 . "MASONRY") (62 . 7) (370 . 13) (100 . "AcDbLine") (10 12104.07239819
444.9462895928 0.0) (11 12104.07239819 452.4886877828 0.0))
((0 . "LINE") (100 . "AcDbEntity") (8 . "MASONRY") (62 . 7) (370 . 13) (100 . "AcDbLine") (10 12219.0808597285
2903.4693099548 0.0) (11 12107.8435972851 2903.4693099548 0.0))
((0 . "LINE") (100 . "AcDbEntity") (8 . "MASONRY") (62 . 7) (370 . 13) (100 . "AcDbLine") (10 12107.8435972851
2756.4097963801 0.0) (11 12322.7757239819 2756.4097963801 0.0))
((0 . "LINE") (100 . "AcDbEntity") (8 . "MASONRY") (62 . 7) (370 . 13) (100 . "AcDbLine") (10 12107.8435972851
2654.599841629 0.0) (11 12138.0090497738 2654.599841629 0.0))
((0 . "LINE") (100 . "AcDbEntity") (8 . "MASONRY") (62 . 7) (370 . 13) (100 . "AcDbLine") (10 12428.3554977376
2584.8416289593 0.0) (11 12281.2966742081 2584.8416289593 0.0))
((0 . "LINE") (100 . "AcDbEntity") (8 . "MASONRY") (62 . 7) (370 . 13) (100 . "AcDbLine") (10 12281.2966742081
2584.8416289593 0.0) (11 12107.8435972851 2584.8416289593 0.0))
((0 . "LINE") (100 . "AcDbEntity") (8 . "MASONRY") (62 . 7) (370 . 13) (100 . "AcDbLine") (10 12107.8435972851
2386.8778280543 0.0) (11 12213.4247511312 2386.8778280543 0.0))
((0 . "LINE") (100 . "AcDbEntity") (8 . "MASONRY") (62 . 7) (370 . 13) (100 . "AcDbLine") (10 12107.8435972851
2247.3607126697 0.0) (11 12413.2734615385 2247.3607126697 0.0))
((0 . "LINE") (100 . "AcDbEntity") (8 . "MASONRY") (62 . 7) (370 . 13) (100 . "AcDbLine") (10 12119.1558144796
1644.0413122172 0.0) (11 12107.8435972851 1644.0413122172 0.0))
((0 . "LINE") (100 . "AcDbEntity") (8 . "MASONRY") (62 . 7) (370 . 13) (100 . "AcDbLine") (10 12209.6535520362
1430.9954751131 0.0) (11 12107.8435972851 1430.9954751131 0.0))
((0 . "LINE") (100 . "AcDbEntity") (8 . "MASONRY") (62 . 7) (370 . 13) (100 . "AcDbLine") (10 12128.5831221719
1242.4589819005 0.0) (11 12107.8435972851 1242.4589819005 0.0))
((0 . "LINE") (100 . "AcDbEntity") (8 . "MASONRY") (62 . 7) (370 . 13) (100 . "AcDbLine") (10 12317.1182352941
1180.2404072398 0.0) (11 12107.8435972851 1180.2404072398 0.0))
((0 . "LINE") (100 . "AcDbEntity") (8 . "MASONRY") (62 . 7) (370 . 13) (100 . "AcDbLine") (10 12107.8435972851
955.8823529412 0.0) (11 12236.0478054299 955.8823529412 0.0))
((0 . "LINE") (100 . "AcDbEntity") (8 . "MASONRY") (62 . 7) (370 . 13) (100 . "AcDbLine") (10 12107.8435972851
788.0853846154 0.0) (11 12285.0678733032 788.0853846154 0.0))
((0 . "LINE") (100 . "AcDbEntity") (8 . "MASONRY") (62 . 7) (370 . 13) (100 . "AcDbLine") (10 12107.8435972851
725.8668099548 0.0) (11 12149.3212669683 725.8668099548 0.0))
((0 . "LINE") (100 . "AcDbEntity") (8 . "MASONRY") (62 . 7) (370 . 13) (100 . "AcDbLine") (10 12319.0045248869
3265.460260181 0.0) (11 12111.6134162896 3265.460260181 0.0))
((0 . "LINE") (100 . "AcDbEntity") (8 . "MASONRY") (62 . 7) (370 . 13) (100 . "AcDbLine") (10 12177.6018099548
3190.0452488688 0.0) (11 12111.6134162896 3190.0452488688 0.0))
((0 . "LINE") (100 . "AcDbEntity") (8 . "MASONRY") (62 . 7) (370 . 13) (100 . "AcDbLine") (10 12187.0291176471
3042.9864253394 0.0) (11 12111.6134162896 3042.9864253394 0.0))
((0 . "LINE") (100 . "AcDbEntity") (8 . "MASONRY") (62 . 7) (370 . 13) (100 . "AcDbLine") (10 12220.9657692308
2997.7375565611 0.0) (11 12220.9657692308 2971.4199434389 0.0))
((0 . "LINE") (100 . "AcDbEntity") (8 . "MASONRY") (62 . 7) (370 . 13) (100 . "AcDbLine") (10 12220.9657692308
2971.4199434389 0.0) (11 12111.6134162896 2971.4199434389 0.0))
((0 . "LINE") (100 . "AcDbEntity") (8 . "MASONRY") (62 . 7) (370 . 13) (100 . "AcDbLine") (10 12324.6606334842
2505.5815384615 0.0) (11 12111.6134162896 2505.5815384615 0.0))
((0 . "LINE") (100 . "AcDbEntity") (8 . "MASONRY") (62 . 7) (370 . 13) (100 . "AcDbLine") (10 12138.0090497738
2303.9217986425 0.0) (11 12111.6134162896 2303.9217986425 0.0))
((0 . "LINE") (100 . "AcDbEntity") (8 . "MASONRY") (62 . 7) (370 . 13) (100 . "AcDbLine") (10 12434.0129864253
1907.9941968326 0.0) (11 12111.6134162896 1907.9941968326 0.0))
((0 . "LINE") (100 . "AcDbEntity") (8 . "MASONRY") (62 . 7) (370 . 13) (100 . "AcDbLine") (10 12111.6134162896
1742.0814479638 0.0) (11 12251.1312217195 1742.0814479638 0.0))
((0 . "LINE") (100 . "AcDbEntity") (8 . "MASONRY") (62 . 7) (370 . 13) (100 . "AcDbLine") (10 12111.6134162896
1595.0226244344 0.0) (11 12424.585678733 1595.0226244344 0.0))
((0 . "LINE") (100 . "AcDbEntity") (8 . "MASONRY") (62 . 7) (370 . 13) (100 . "AcDbLine") (10 12111.6134162896
1033.1815837104 0.0) (11 12317.7203054299 1033.1815837104 0.0))
((0 . "LINE") (100 . "AcDbEntity") (8 . "MASONRY") (62 . 7) (370 . 13) (100 . "AcDbLine") (10 12122.9256334842
586.3503846154 0.0) (11 12111.6134162896 586.3503846154 0.0))
((0 . "LINE") (100 . "AcDbEntity") (8 . "MASONRY") (62 . 7) (370 . 13) (100 . "AcDbLine") (10 12307.6923076923
1242.4589819005 0.0) (11 12128.5831221719 1242.4589819005 0.0))
((0 . "LINE") (100 . "AcDbEntity") (8 . "MASONRY") (62 . 7) (370 . 13) (100 . "AcDbLine") (10 12128.5831221719
1242.4589819005 0.0) (11 12128.5831221719 1278.2805429864 0.0))
((0 . "LINE") (100 . "AcDbEntity") (8 . "MASONRY") (62 . 7) (370 . 13) (100 . "AcDbLine") (10 12126.6968325792
321.9307579186 0.0) (11 12141.0552828054 321.9307579186 0.0))
((0 . "LINE") (100 . "AcDbEntity") (8 . "MASONRY") (62 . 7) (370 . 13) (100 . "AcDbLine") (10 12130.4680316742
1344.2689366516 0.0) (11 12130.4680316742 1323.5294117647 0.0))
((0 . "LINE") (100 . "AcDbEntity") (8 . "MASONRY") (62 . 7) (370 . 13) (100 . "AcDbLine") (10 12718.7033257919
1344.2689366516 0.0) (11 12130.4680316742 1344.2689366516 0.0))
((0 . "LINE") (100 . "AcDbEntity") (8 . "MASONRY") (62 . 7) (370 . 13) (100 . "AcDbLine") (10 12134.2378506787
2714.9321266968 0.0) (11 12134.2378506787 2722.4738348416 0.0))
((0 . "LINE") (100 . "AcDbEntity") (8 . "MASONRY") (62 . 7) (370 . 13) (100 . "AcDbLine") (10 12428.3554977376
2630.0904977376 0.0) (11 12138.0090497738 2630.0904977376 0.0))
((0 . "LINE") (100 . "AcDbEntity") (8 . "MASONRY") (62 . 7) (370 . 13) (100 . "AcDbLine") (10 12138.0090497738
2630.0904977376 0.0) (11 12138.0090497738 2654.599841629 0.0))
((0 . "LINE") (100 . "AcDbEntity") (8 . "MASONRY") (62 . 7) (370 . 13) (100 . "AcDbLine") (10 12138.0090497738
2669.6832579186 0.0) (11 12138.0090497738 2654.599841629 0.0))
((0 . "LINE") (100 . "AcDbEntity") (8 . "MASONRY") (62 . 7) (370 . 13) (100 . "AcDbLine") (10 12141.7802488688
2032.4285859729 0.0) (11 12134.2378506787 2032.4285859729 0.0))
((0 . "LINE") (100 . "AcDbEntity") (8 . "MASONRY") (62 . 7) (370 . 13) (100 . "AcDbLine") (10 12127.8982013575
223.4149095023 0.0) (11 12122.2448529412 223.4149095023 0.0))
((0 . "LINE") (100 . "AcDbEntity") (8 . "MASONRY") (62 . 7) (370 . 13) (100 . "AcDbLine") (10 12153.0924660634
2303.9217986425 0.0) (11 12138.0090497738 2303.9217986425 0.0))
((0 . "LINE") (100 . "AcDbEntity") (8 . "MASONRY") (62 . 7) (370 . 13) (100 . "AcDbLine") (10 12256.7873303167
2303.9217986425 0.0) (11 12153.0924660634 2303.9217986425 0.0))
((0 . "LINE") (100 . "AcDbEntity") (8 . "MASONRY") (62 . 7) (370 . 13) (100 . "AcDbLine") (10 12247.3600226244
1666.5124660633 0.0) (11 12164.4046832579 1666.5124660633 0.0))
((0 . "LINE") (100 . "AcDbEntity") (8 . "MASONRY") (62 . 7) (370 . 13) (100 . "AcDbLine") (10 12164.4046832579
1666.5124660633 0.0) (11 12141.7802488688 1666.5124660633 0.0))
((0 . "LINE") (100 . "AcDbEntity") (8 . "MASONRY") (62 . 7) (370 . 13) (100 . "AcDbLine") (10 12175.7169004525
3386.1234502262 0.0) (11 12254.9024208145 3386.1234502262 0.0))
((0 . "LINE") (100 . "AcDbEntity") (8 . "MASONRY") (62 . 7) (370 . 13) (100 . "AcDbLine") (10 12481.1467647059
3190.0452488688 0.0) (11 12285.0678733032 3190.0452488688 0.0))
((0 . "LINE") (100 . "AcDbEntity") (8 . "MASONRY") (62 . 7) (370 . 13) (100 . "AcDbLine") (10 12285.0678733032
3190.0452488688 0.0) (11 12177.6018099548 3190.0452488688 0.0))
((0 . "LINE") (100 . "AcDbEntity") (8 . "MASONRY") (62 . 7) (370 . 13) (100 . "AcDbLine") (10 12177.6018099548
3212.6696832579 0.0) (11 12177.6018099548 3190.0452488688 0.0))
((0 . "LINE") (100 . "AcDbEntity") (8 . "MASONRY") (62 . 7) (370 . 13) (100 . "AcDbLine") (10 12175.7169004525
2036.1990950226 0.0) (11 12183.257918552 2036.1990950226 0.0))
((0 . "LINE") (100 . "AcDbEntity") (8 . "MASONRY") (62 . 7) (370 . 13) (100 . "AcDbLine") (10 12185.1442081448
554.2986425339 0.0) (11 12185.1442081448 588.2352941176 0.0))
((0 . "LINE") (100 . "AcDbEntity") (8 . "MASONRY") (62 . 7) (370 . 13) (100 . "AcDbLine") (10 12183.257918552
2036.1990950226 0.0) (11 12183.257918552 2021.1163687783 0.0))
((0 . "LINE") (100 . "AcDbEntity") (8 . "MASONRY") (62 . 7) (370 . 13) (100 . "AcDbLine") (10 12183.257918552
2036.1990950226 0.0) (11 12203.9960633484 2036.1990950226 0.0))
((0 . "LINE") (100 . "AcDbEntity") (8 . "MASONRY") (62 . 7) (370 . 13) (100 . "AcDbLine") (10 12420.814479638
2088.9896719457 0.0) (11 12198.3413348416 2088.9896719457 0.0))
((0 . "LINE") (100 . "AcDbEntity") (8 . "MASONRY") (62 . 7) (370 . 13) (100 . "AcDbLine") (10 12198.3413348416
727.751719457 0.0) (11 12277.5268552036 727.751719457 0.0))
((0 . "LINE") (100 . "AcDbEntity") (8 . "MASONRY") (62 . 7) (370 . 13) (100 . "AcDbLine") (10 12203.9960633484
2051.281821267 0.0) (11 12203.9960633484 2036.1990950226 0.0))
((0 . "LINE") (100 . "AcDbEntity") (8 . "MASONRY") (62 . 7) (370 . 13) (100 . "AcDbLine") (10 12251.1312217195
3525.6412556561 0.0) (11 12205.8823529412 3525.6412556561 0.0))
((0 . "LINE") (100 . "AcDbEntity") (8 . "MASONRY") (62 . 7) (370 . 13) (100 . "AcDbLine") (10 12349.1699773756
2036.1990950226 0.0) (11 12203.9960633484 2036.1990950226 0.0))
((0 . "LINE") (100 . "AcDbEntity") (8 . "MASONRY") (62 . 7) (370 . 13) (100 . "AcDbLine") (10 12213.4247511312
2386.8778280543 0.0) (11 12213.4247511312 2360.4828846154 0.0))
((0 . "LINE") (100 . "AcDbEntity") (8 . "MASONRY") (62 . 7) (370 . 13) (100 . "AcDbLine") (10 12537.7078506787
3044.8713348416 0.0) (11 12217.1945701357 3044.8713348416 0.0))
((0 . "LINE") (100 . "AcDbEntity") (8 . "MASONRY") (62 . 7) (370 . 13) (100 . "AcDbLine") (10 12219.0808597285
2903.4693099548 0.0) (11 12224.7355882353 2903.4693099548 0.0))
((0 . "LINE") (100 . "AcDbEntity") (8 . "MASONRY") (62 . 7) (370 . 13) (100 . "AcDbLine") (10 12219.0808597285
2903.4693099548 0.0) (11 12219.0808597285 2937.4059615385 0.0))
((0 . "LINE") (100 . "AcDbEntity") (8 . "MASONRY") (62 . 7) (370 . 13) (100 . "AcDbLine") (10 12213.4247511312
2386.8778280543 0.0) (11 12254.9051809955 2386.8778280543 0.0))
((0 . "LINE") (100 . "AcDbEntity") (8 . "MASONRY") (62 . 7) (370 . 13) (100 . "AcDbLine") (10 12254.9051809955
2386.8778280543 0.0) (11 12254.9051809955 2368.1019230769 0.0))
((0 . "LINE") (100 . "AcDbEntity") (8 . "MASONRY") (62 . 7) (370 . 13) (100 . "AcDbLine") (10 12254.9051809955
2368.1019230769 0.0) (11 12533.9366515837 2368.1019230769 0.0))
((0 . "LINE") (100 . "AcDbEntity") (8 . "MASONRY") (62 . 7) (370 . 13) (100 . "AcDbLine") (10 12579.185520362
1436.6515837104 0.0) (11 12232.2779864253 1436.6515837104 0.0))
((0 . "LINE") (100 . "AcDbEntity") (8 . "MASONRY") (62 . 7) (370 . 13) (100 . "AcDbLine") (10 12239.8190045249
590.1202036199 0.0) (11 12266.2146380091 590.1202036199 0.0))
((0 . "LINE") (100 . "AcDbEntity") (8 . "MASONRY") (62 . 7) (370 . 13) (100 . "AcDbLine") (10 12386.8778280543
1817.4971493213 0.0) (11 12247.3600226244 1817.4971493213 0.0))
((0 . "LINE") (100 . "AcDbEntity") (8 . "MASONRY") (62 . 7) (370 . 13) (100 . "AcDbLine") (10 12251.1312217195
957.6913122172 0.0) (11 12430.2404072398 957.6913122172 0.0))
((0 . "LINE") (100 . "AcDbEntity") (8 . "MASONRY") (62 . 7) (370 . 13) (100 . "AcDbLine") (10 12430.2404072398
957.6913122172 0.0) (11 12430.2404072398 901.8096266968 0.0))
((0 . "LINE") (100 . "AcDbEntity") (8 . "MASONRY") (62 . 7) (370 . 13) (100 . "AcDbLine") (10 12430.2404072398
901.8096266968 0.0) (11 12500 901.8096266968 0.0))
((0 . "LINE") (100 . "AcDbEntity") (8 . "MASONRY") (62 . 7) (370 . 13) (100 . "AcDbLine") (10 12256.7873303167
2303.9217986425 0.0) (11 12281.2966742081 2303.9217986425 0.0))
((0 . "LINE") (100 . "AcDbEntity") (8 . "MASONRY") (62 . 7) (370 . 13) (100 . "AcDbLine") (10 12256.7873303167
2326.5462330317 0.0) (11 12256.7873303167 2303.9217986425 0.0))
((0 . "LINE") (100 . "AcDbEntity") (8 . "MASONRY") (62 . 7) (370 . 13) (100 . "AcDbLine") (10 12405.7310633484
2899.6981108597 0.0) (11 12258.672239819 2899.6981108597 0.0))
((0 . "LINE") (100 . "AcDbEntity") (8 . "MASONRY") (62 . 7) (370 . 13) (100 . "AcDbLine") (10 12266.2132579186
837.1040723982 0.0) (11 12266.2132579186 861.5347058824 0.0))
((0 . "LINE") (100 . "AcDbEntity") (8 . "MASONRY") (62 . 7) (370 . 13) (100 . "AcDbLine") (10 12266.2132579186
861.5347058824 0.0) (11 12321.085520362 861.5347058824 0.0))
((0 . "LINE") (100 . "AcDbEntity") (8 . "MASONRY") (62 . 7) (370 . 13) (100 . "AcDbLine") (10 12327.3878846154
865.3832352941 0.0) (11 12496.228800905 865.3832352941 0.0))
((0 . "LINE") (100 . "AcDbEntity") (8 . "MASONRY") (62 . 7) (370 . 13) (100 . "AcDbLine") (10 12268.0995475113
1466.8184162896 0.0) (11 12268.0995475113 1474.3580542986 0.0))
((0 . "LINE") (100 . "AcDbEntity") (8 . "MASONRY") (62 . 7) (370 . 13) (100 . "AcDbLine") (10 12426.4705882353
1530.9191402715 0.0) (11 12269.9844570136 1530.9191402715 0.0))
((0 . "LINE") (100 . "AcDbEntity") (8 . "MASONRY") (62 . 7) (370 . 13) (100 . "AcDbLine") (10 12286.9541628959
2417.0439705882 0.0) (11 12286.9541628959 2398.1900452489 0.0))
((0 . "LINE") (100 . "AcDbEntity") (8 . "MASONRY") (62 . 7) (370 . 13) (100 . "AcDbLine") (10 12281.2966742081
3141.0258710407 0.0) (11 12281.2966742081 3152.3380882353 0.0))
((0 . "LINE") (100 . "AcDbEntity") (8 . "MASONRY") (62 . 7) (370 . 13) (100 . "AcDbLine") (10 12458.5223303167
1749.4753959276 0.0) (11 12311.4635067873 1749.4753959276 0.0))
((0 . "LINE") (100 . "AcDbEntity") (8 . "MASONRY") (62 . 7) (370 . 13) (100 . "AcDbLine") (10 12311.4635067873
1749.4753959276 0.0) (11 12281.2966742081 1749.4753959276 0.0))
((0 . "LINE") (100 . "AcDbEntity") (8 . "MASONRY") (62 . 7) (370 . 13) (100 . "AcDbLine") (10 12285.0678733032
1668.5520361991 0.0) (11 12296.3800904977 1668.5520361991 0.0))
((0 . "LINE") (100 . "AcDbEntity") (8 . "MASONRY") (62 . 7) (370 . 13) (100 . "AcDbLine") (10 12285.0678733032
818.2494570136 0.0) (11 12285.0678733032 788.0853846154 0.0))
((0 . "LINE") (100 . "AcDbEntity") (8 . "MASONRY") (62 . 7) (370 . 13) (100 . "AcDbLine") (10 12526.3956334842
788.0853846154 0.0) (11 12412.9310067873 788.0853846154 0.0))
((0 . "LINE") (100 . "AcDbEntity") (8 . "MASONRY") (62 . 7) (370 . 13) (100 . "AcDbLine") (10 12342.3981108597
788.0853846154 0.0) (11 12285.0678733032 788.0853846154 0.0))
((0 . "LINE") (100 . "AcDbEntity") (8 . "MASONRY") (62 . 7) (370 . 13) (100 . "AcDbLine") (10 12492.4589819005
3103.3187104072 0.0) (11 12288.8390723982 3103.3187104072 0.0))
((0 . "LINE") (100 . "AcDbEntity") (8 . "MASONRY") (62 . 7) (370 . 13) (100 . "AcDbLine") (10 12288.8390723982
2473.6050565611 0.0) (11 12288.8390723982 2462.2928393665 0.0))
((0 . "LINE") (100 . "AcDbEntity") (8 . "MASONRY") (62 . 7) (370 . 13) (100 . "AcDbLine") (10 12296.3800904977
1662.8959276018 0.0) (11 12296.3800904977 1668.5520361991 0.0))
((0 . "LINE") (100 . "AcDbEntity") (8 . "MASONRY") (62 . 7) (370 . 13) (100 . "AcDbLine") (10 12296.3800904977
1708.1447963801 0.0) (11 12296.3800904977 1668.5520361991 0.0))
((0 . "LINE") (100 . "AcDbEntity") (8 . "MASONRY") (62 . 7) (370 . 13) (100 . "AcDbLine") (10 12513.1971266968
2824.2837895928 0.0) (11 12296.3800904977 2824.2837895928 0.0))
((0 . "LINE") (100 . "AcDbEntity") (8 . "MASONRY") (62 . 7) (370 . 13) (100 . "AcDbLine") (10 12303.9211085973
726.4723303167 0.0) (11 12322.7715837104 726.4723303167 0.0))
((0 . "LINE") (100 . "AcDbEntity") (8 . "MASONRY") (62 . 7) (370 . 13) (100 . "AcDbLine") (10 12322.7715837104
726.4723303167 0.0) (11 12322.7715837104 746.6063348416 0.0))
((0 . "LINE") (100 . "AcDbEntity") (8 . "MASONRY") (62 . 7) (370 . 13) (100 . "AcDbLine") (10 12307.6923076923
1242.4589819005 0.0) (11 12307.6923076923 1217.949638009 0.0))
((0 . "LINE") (100 . "AcDbEntity") (8 . "MASONRY") (62 . 7) (370 . 13) (100 . "AcDbLine") (10 12714.9321266968
1242.4589819005 0.0) (11 12594.2689366516 1242.4589819005 0.0))
((0 . "LINE") (100 . "AcDbEntity") (8 . "MASONRY") (62 . 7) (370 . 13) (100 . "AcDbLine") (10 12594.2689366516
1242.4589819005 0.0) (11 12564.1021040724 1242.4589819005 0.0))
((0 . "LINE") (100 . "AcDbEntity") (8 . "MASONRY") (62 . 7) (370 . 13) (100 . "AcDbLine") (10 12564.1021040724
1242.4589819005 0.0) (11 12477.3755656109 1242.4589819005 0.0))
((0 . "LINE") (100 . "AcDbEntity") (8 . "MASONRY") (62 . 7) (370 . 13) (100 . "AcDbLine") (10 12477.3755656109
1242.4589819005 0.0) (11 12307.6923076923 1242.4589819005 0.0))
((0 . "LINE") (100 . "AcDbEntity") (8 . "MASONRY") (62 . 7) (370 . 13) (100 . "AcDbLine") (10 12718.7033257919
2300.1505995475 0.0) (11 12311.4635067873 2300.1505995475 0.0))
((0 . "LINE") (100 . "AcDbEntity") (8 . "MASONRY") (62 . 7) (370 . 13) (100 . "AcDbLine") (10 12428.3554977376
1282.050361991 0.0) (11 12394.4188461538 1282.050361991 0.0))
((0 . "LINE") (100 . "AcDbEntity") (8 . "MASONRY") (62 . 7) (370 . 13) (100 . "AcDbLine") (10 12394.4188461538
1282.050361991 0.0) (11 12311.4635067873 1282.050361991 0.0))
((0 . "LINE") (100 . "AcDbEntity") (8 . "MASONRY") (62 . 7) (370 . 13) (100 . "AcDbLine") (10 12319.0045248869
3389.8946493213 0.0) (11 12337.857760181 3389.8946493213 0.0))
((0 . "LINE") (100 . "AcDbEntity") (8 . "MASONRY") (62 . 7) (370 . 13) (100 . "AcDbLine") (10 12319.0045248869
3389.8946493213 0.0) (11 12319.0045248869 3337.1040723982 0.0))
((0 . "LINE") (100 . "AcDbEntity") (8 . "MASONRY") (62 . 7) (370 . 13) (100 . "AcDbLine") (10 12319.0045248869
3389.8946493213 0.0) (11 12319.0045248869 3423.831300905 0.0))
((0 . "LINE") (100 . "AcDbEntity") (8 . "MASONRY") (62 . 7) (370 . 13) (100 . "AcDbLine") (10 12317.1182352941
1180.2404072398 0.0) (11 12317.1182352941 1116.1396832579 0.0))
((0 . "LINE") (100 . "AcDbEntity") (8 . "MASONRY") (62 . 7) (370 . 13) (100 . "AcDbLine") (10 12317.1182352941
1180.2404072398 0.0) (11 12533.9366515837 1180.2404072398 0.0))
((0 . "LINE") (100 . "AcDbEntity") (8 . "MASONRY") (62 . 7) (370 . 13) (100 . "AcDbLine") (10 12334.0879411765
1033.1815837104 0.0) (11 12317.7203054299 1033.1815837104 0.0))
((0 . "LINE") (100 . "AcDbEntity") (8 . "MASONRY") (62 . 7) (370 . 13) (100 . "AcDbLine") (10 12598.0387556561
1082.054581448 0.0) (11 12345.400158371 1082.054581448 0.0))
((0 . "LINE") (100 . "AcDbEntity") (8 . "MASONRY") (62 . 7) (370 . 13) (100 . "AcDbLine") (10 12345.400158371
1082.054581448 0.0) (11 12317.7203054299 1082.054581448 0.0))
((0 . "LINE") (100 . "AcDbEntity") (8 . "MASONRY") (62 . 7) (370 . 13) (100 . "AcDbLine") (10 12317.7203054299
1082.054581448 0.0) (11 12317.7203054299 1033.1815837104 0.0))
((0 . "LINE") (100 . "AcDbEntity") (8 . "MASONRY") (62 . 7) (370 . 13) (100 . "AcDbLine") (10 12319.0045248869
3306.9379298643 0.0) (11 12319.0045248869 3265.460260181 0.0))
((0 . "LINE") (100 . "AcDbEntity") (8 . "MASONRY") (62 . 7) (370 . 13) (100 . "AcDbLine") (10 12541.4776696833
3265.460260181 0.0) (11 12319.0045248869 3265.460260181 0.0))
((0 . "LINE") (100 . "AcDbEntity") (8 . "MASONRY") (62 . 7) (370 . 13) (100 . "AcDbLine") (10 12319.0045248869
678.7330316742 0.0) (11 12319.0045248869 656.1085972851 0.0))
((0 . "LINE") (100 . "AcDbEntity") (8 . "MASONRY") (62 . 7) (370 . 13) (100 . "AcDbLine") (10 12322.7757239819
2790.3471380091 0.0) (11 12322.7757239819 2756.4097963801 0.0))
((0 . "LINE") (100 . "AcDbEntity") (8 . "MASONRY") (62 . 7) (370 . 13) (100 . "AcDbLine") (10 12426.4705882353
2756.4097963801 0.0) (11 12322.7757239819 2756.4097963801 0.0))
((0 . "LINE") (100 . "AcDbEntity") (8 . "MASONRY") (62 . 7) (370 . 13) (100 . "AcDbLine") (10 12324.6606334842
2505.5815384615 0.0) (11 12324.6606334842 2556.5610859729 0.0))
((0 . "LINE") (100 . "AcDbEntity") (8 . "MASONRY") (62 . 7) (370 . 13) (100 . "AcDbLine") (10 12575.414321267
2505.5815384615 0.0) (11 12533.9366515837 2505.5815384615 0.0))
((0 . "LINE") (100 . "AcDbEntity") (8 . "MASONRY") (62 . 7) (370 . 13) (100 . "AcDbLine") (10 12533.9366515837
2505.5815384615 0.0) (11 12324.6606334842 2505.5815384615 0.0))
((0 . "LINE") (100 . "AcDbEntity") (8 . "MASONRY") (62 . 7) (370 . 13) (100 . "AcDbLine") (10 12326.5455429864
584.4654751131 0.0) (11 12326.5455429864 550.5288235294 0.0))
((0 . "LINE") (100 . "AcDbEntity") (8 . "MASONRY") (62 . 7) (370 . 13) (100 . "AcDbLine") (10 12332.2030316742
2209.6528619909 0.0) (11 12332.2030316742 2164.4039932127 0.0))
((0 . "LINE") (100 . "AcDbEntity") (8 . "MASONRY") (62 . 7) (370 . 13) (100 . "AcDbLine") (10 12535.7483710407
3374.8112330317 0.0) (11 12535.7483710407 3419.3841628959 0.0))
((0 . "LINE") (100 . "AcDbEntity") (8 . "MASONRY") (62 . 7) (370 . 13) (100 . "AcDbLine") (10 12535.7483710407
3419.3841628959 0.0) (11 12356.7123755656 3419.3841628959 0.0))
((0 . "LINE") (100 . "AcDbEntity") (8 . "MASONRY") (62 . 7) (370 . 13) (100 . "AcDbLine") (10 12356.7123755656
2113.4997058824 0.0) (11 12368.0245927602 2113.4997058824 0.0))
((0 . "LINE") (100 . "AcDbEntity") (8 . "MASONRY") (62 . 7) (370 . 13) (100 . "AcDbLine") (10 12360.4821945701
1029.4117647059 0.0) (11 12390.6490271493 1029.4117647059 0.0))
((0 . "LINE") (100 . "AcDbEntity") (8 . "MASONRY") (62 . 7) (370 . 13) (100 . "AcDbLine") (10 12368.0245927602
1393.2876244344 0.0) (11 12375.5656108597 1393.2876244344 0.0))
((0 . "LINE") (100 . "AcDbEntity") (8 . "MASONRY") (62 . 7) (370 . 13) (100 . "AcDbLine") (10 12383.1066289593
2043.7408031674 0.0) (11 12511.3122171946 2043.7408031674 0.0))
((0 . "LINE") (100 . "AcDbEntity") (8 . "MASONRY") (62 . 7) (370 . 13) (100 . "AcDbLine") (10 12417.043280543
2895.92760181 0.0) (11 12541.4776696833 2895.92760181 0.0))
((0 . "LINE") (100 . "AcDbEntity") (8 . "MASONRY") (62 . 7) (370 . 13) (100 . "AcDbLine") (10 12432.1266968326
2088.9896719457 0.0) (11 12420.814479638 2088.9896719457 0.0))
((0 . "LINE") (100 . "AcDbEntity") (8 . "MASONRY") (62 . 7) (370 . 13) (100 . "AcDbLine") (10 12420.814479638
2130.467341629 0.0) (11 12420.814479638 2088.9896719457 0.0))
((0 . "LINE") (100 . "AcDbEntity") (8 . "MASONRY") (62 . 7) (370 . 13) (100 . "AcDbLine") (10 12417.043280543
1817.4971493213 0.0) (11 12469.8345475113 1817.4971493213 0.0))
((0 . "LINE") (100 . "AcDbEntity") (8 . "MASONRY") (62 . 7) (370 . 13) (100 . "AcDbLine") (10 12420.814479638
1474.3580542986 0.0) (11 12420.814479638 1504.5248868778 0.0))
((0 . "LINE") (100 . "AcDbEntity") (8 . "MASONRY") (62 . 7) (370 . 13) (100 . "AcDbLine") (10 12426.4705882353
2756.4097963801 0.0) (11 12426.4705882353 2711.1616176471 0.0))
((0 . "LINE") (100 . "AcDbEntity") (8 . "MASONRY") (62 . 7) (370 . 13) (100 . "AcDbLine") (10 12426.4705882353
2756.4097963801 0.0) (11 12533.9366515837 2756.4097963801 0.0))
((0 . "LINE") (100 . "AcDbEntity") (8 . "MASONRY") (62 . 7) (370 . 13) (100 . "AcDbLine") (10 12628.2042081448
2209.6528619909 0.0) (11 12424.585678733 2209.6528619909 0.0))
((0 . "LINE") (100 . "AcDbEntity") (8 . "MASONRY") (62 . 7) (370 . 13) (100 . "AcDbLine") (10 12432.1266968326
1530.9191402715 0.0) (11 12426.4705882353 1530.9191402715 0.0))
((0 . "LINE") (100 . "AcDbEntity") (8 . "MASONRY") (62 . 7) (370 . 13) (100 . "AcDbLine") (10 12426.4705882353
1530.9191402715 0.0) (11 12426.4705882353 1561.0859728507 0.0))
((0 . "LINE") (100 . "AcDbEntity") (8 . "MASONRY") (62 . 7) (370 . 13) (100 . "AcDbLine") (10 12428.3554977376
2630.0904977376 0.0) (11 12428.3554977376 2662.1415497738 0.0))
((0 . "LINE") (100 . "AcDbEntity") (8 . "MASONRY") (62 . 7) (370 . 13) (100 . "AcDbLine") (10 12428.3554977376
2584.8416289593 0.0) (11 12507.5410180995 2584.8416289593 0.0))
((0 . "LINE") (100 . "AcDbEntity") (8 . "MASONRY") (62 . 7) (370 . 13) (100 . "AcDbLine") (10 12428.3554977376
2584.8416289593 0.0) (11 12428.3554977376 2630.0904977376 0.0))
((0 . "LINE") (100 . "AcDbEntity") (8 . "MASONRY") (62 . 7) (370 . 13) (100 . "AcDbLine") (10 12435.8978959276
1034.4395701357 0.0) (11 12428.3554977376 1034.4395701357 0.0))
((0 . "LINE") (100 . "AcDbEntity") (8 . "MASONRY") (62 . 7) (370 . 13) (100 . "AcDbLine") (10 12484.9165837104
737.1790271493 0.0) (11 12469.8345475113 737.1790271493 0.0))
((0 . "LINE") (100 . "AcDbEntity") (8 . "MASONRY") (62 . 7) (370 . 13) (100 . "AcDbLine") (10 12428.3554977376
2630.0904977376 0.0) (11 12533.9366515837 2630.0904977376 0.0))
((0 . "LINE") (100 . "AcDbEntity") (8 . "MASONRY") (62 . 7) (370 . 13) (100 . "AcDbLine") (10 12434.0129864253
1907.9941968326 0.0) (11 12628.2055882353 1907.9941968326 0.0))
((0 . "LINE") (100 . "AcDbEntity") (8 . "MASONRY") (62 . 7) (370 . 13) (100 . "AcDbLine") (10 12628.2055882353
1907.9941968326 0.0) (11 12628.2055882353 1926.8474321267 0.0))
((0 . "LINE") (100 . "AcDbEntity") (8 . "MASONRY") (62 . 7) (370 . 13) (100 . "AcDbLine") (10 12434.0129864253
1923.0769230769 0.0) (11 12434.0129864253 1907.9941968326 0.0))
((0 . "LINE") (100 . "AcDbEntity") (8 . "MASONRY") (62 . 7) (370 . 13) (100 . "AcDbLine") (10 12435.8978959276
1874.0575452489 0.0) (11 12435.8978959276 1862.7453280543 0.0))
((0 . "LINE") (100 . "AcDbEntity") (8 . "MASONRY") (62 . 7) (370 . 13) (100 . "AcDbLine") (10 12435.8978959276
997.4373529412 0.0) (11 12639.5178054299 997.4373529412 0.0))
((0 . "LINE") (100 . "AcDbEntity") (8 . "MASONRY") (62 . 7) (370 . 13) (100 . "AcDbLine") (10 12639.5178054299
997.4373529412 0.0) (11 12639.5178054299 1052.036199095 0.0))
((0 . "LINE") (100 . "AcDbEntity") (8 . "MASONRY") (62 . 7) (370 . 13) (100 . "AcDbLine") (10 12466.0633484163
2088.9896719457 0.0) (11 12560.3322850679 2088.9896719457 0.0))
((0 . "LINE") (100 . "AcDbEntity") (8 . "MASONRY") (62 . 7) (370 . 13) (100 . "AcDbLine") (10 12522.6244343891
1596.9075339367 0.0) (11 12469.8345475113 1596.9075339367 0.0))
((0 . "LINE") (100 . "AcDbEntity") (8 . "MASONRY") (62 . 7) (370 . 13) (100 . "AcDbLine") (10 12469.8345475113
1568.6269909502 0.0) (11 12865.7621493213 1568.6269909502 0.0))
((0 . "LINE") (100 . "AcDbEntity") (8 . "MASONRY") (62 . 7) (370 . 13) (100 . "AcDbLine") (10 12571.6445022624
1817.4971493213 0.0) (11 12481.1467647059 1817.4971493213 0.0))
((0 . "LINE") (100 . "AcDbEntity") (8 . "MASONRY") (62 . 7) (370 . 13) (100 . "AcDbLine") (10 12492.45760181
1693.062760181 0.0) (11 12492.45760181 1644.0413122172 0.0))
((0 . "LINE") (100 . "AcDbEntity") (8 . "MASONRY") (62 . 7) (370 . 13) (100 . "AcDbLine") (10 12488.6877828054
1749.6238461538 0.0) (11 12503.771199095 1749.6238461538 0.0))
((0 . "LINE") (100 . "AcDbEntity") (8 . "MASONRY") (62 . 7) (370 . 13) (100 . "AcDbLine") (10 12549.0200678733
708.0533823529 0.0) (11 12501.0425678733 708.0533823529 0.0))
((0 . "LINE") (100 . "AcDbEntity") (8 . "MASONRY") (62 . 7) (370 . 13) (100 . "AcDbLine") (10 12503.771199095
1760.9360633484 0.0) (11 12503.771199095 1749.6238461538 0.0))
((0 . "LINE") (100 . "AcDbEntity") (8 . "MASONRY") (62 . 7) (370 . 13) (100 . "AcDbLine") (10 12503.771199095
1749.6238461538 0.0) (11 12530.1654524887 1749.6238461538 0.0))
((0 . "LINE") (100 . "AcDbEntity") (8 . "MASONRY") (62 . 7) (370 . 13) (100 . "AcDbLine") (10 12513.1971266968
2858.2204411765 0.0) (11 12513.1971266968 2824.2837895928 0.0))
((0 . "LINE") (100 . "AcDbEntity") (8 . "MASONRY") (62 . 7) (370 . 13) (100 . "AcDbLine") (10 12513.1971266968
2824.2837895928 0.0) (11 12541.4776696833 2824.2837895928 0.0))
((0 . "LINE") (100 . "AcDbEntity") (8 . "MASONRY") (62 . 7) (370 . 13) (100 . "AcDbLine") (10 12590.4977375566
1042.6088914027 0.0) (11 12515.0834162896 1042.6088914027 0.0))
((0 . "LINE") (100 . "AcDbEntity") (8 . "MASONRY") (62 . 7) (370 . 13) (100 . "AcDbLine") (10 12518.8532352941
2582.9560294118 0.0) (11 12537.7078506787 2582.9560294118 0.0))
((0 . "LINE") (100 . "AcDbEntity") (8 . "MASONRY") (62 . 7) (370 . 13) (100 . "AcDbLine") (10 12528.2805429864
859.7285067873 0.0) (11 12528.2805429864 871.0407239819 0.0))
((0 . "LINE") (100 . "AcDbEntity") (8 . "MASONRY") (62 . 7) (370 . 13) (100 . "AcDbLine") (10 12526.3956334842
788.0853846154 0.0) (11 12526.3956334842 844.6464705882 0.0))
((0 . "LINE") (100 . "AcDbEntity") (8 . "MASONRY") (62 . 7) (370 . 13) (100 . "AcDbLine") (10 12526.3956334842
788.0853846154 0.0) (11 12537.7078506787 788.0853846154 0.0))
((0 . "LINE") (100 . "AcDbEntity") (8 . "MASONRY") (62 . 7) (370 . 13) (100 . "AcDbLine") (10 12530.1654524887
904.9773755656 0.0) (11 12541.4776696833 904.9773755656 0.0))
((0 . "LINE") (100 . "AcDbEntity") (8 . "MASONRY") (62 . 7) (370 . 13) (100 . "AcDbLine") (10 12533.9366515837
3171.1913235294 0.0) (11 12533.9366515837 3190.0452488688 0.0))
((0 . "LINE") (100 . "AcDbEntity") (8 . "MASONRY") (62 . 7) (370 . 13) (100 . "AcDbLine") (10 12533.9366515837
3190.0452488688 0.0) (11 12533.9366515837 3220.2113914027 0.0))
((0 . "LINE") (100 . "AcDbEntity") (8 . "MASONRY") (62 . 7) (370 . 13) (100 . "AcDbLine") (10 12537.7078506787
3118.4014366516 0.0) (11 12537.7078506787 3133.4841628959 0.0))
((0 . "LINE") (100 . "AcDbEntity") (8 . "MASONRY") (62 . 7) (370 . 13) (100 . "AcDbLine") (10 12539.592760181
2944.946979638 0.0) (11 12539.592760181 2993.9670475113 0.0))
((0 . "LINE") (100 . "AcDbEntity") (8 . "MASONRY") (62 . 7) (370 . 13) (100 . "AcDbLine") (10 12537.7078506787
2533.9366515837 0.0) (11 12537.7078506787 2526.3949434389 0.0))
((0 . "LINE") (100 . "AcDbEntity") (8 . "MASONRY") (62 . 7) (370 . 13) (100 . "AcDbLine") (10 12552.7898868778
2254.9017307692 0.0) (11 12537.7078506787 2254.9017307692 0.0))
((0 . "LINE") (100 . "AcDbEntity") (8 . "MASONRY") (62 . 7) (370 . 13) (100 . "AcDbLine") (10 12541.4776696833
3310.7091289593 0.0) (11 12541.4776696833 3359.7285067873 0.0))
((0 . "LINE") (100 . "AcDbEntity") (8 . "MASONRY") (62 . 7) (370 . 13) (100 . "AcDbLine") (10 12549.0200678733
1762.1395022624 0.0) (11 12843.1377149321 1762.1395022624 0.0))
((0 . "LINE") (100 . "AcDbEntity") (8 . "MASONRY") (62 . 7) (370 . 13) (100 . "AcDbLine") (10 12843.1377149321
1762.1395022624 0.0) (11 12858.2197511312 1762.1395022624 0.0))
((0 . "LINE") (100 . "AcDbEntity") (8 . "MASONRY") (62 . 7) (370 . 13) (100 . "AcDbLine") (10 12549.0200678733
1598.8704638009 0.0) (11 12726.2415837104 1598.8704638009 0.0))
((0 . "LINE") (100 . "AcDbEntity") (8 . "MASONRY") (62 . 7) (370 . 13) (100 . "AcDbLine") (10 12726.2415837104
1598.8704638009 0.0) (11 12726.2415837104 1632.7290950226 0.0))
((0 . "LINE") (100 . "AcDbEntity") (8 . "MASONRY") (62 . 7) (370 . 13) (100 . "AcDbLine") (10 12552.7898868778
1184.0129864253 0.0) (11 12586.7265384615 1184.0129864253 0.0))
((0 . "LINE") (100 . "AcDbEntity") (8 . "MASONRY") (62 . 7) (370 . 13) (100 . "AcDbLine") (10 12564.1021040724
2043.7408031674 0.0) (11 12556.5610859729 2043.7408031674 0.0))
((0 . "LINE") (100 . "AcDbEntity") (8 . "MASONRY") (62 . 7) (370 . 13) (100 . "AcDbLine") (10 12560.3322850679
2088.9896719457 0.0) (11 12560.3322850679 2070.1357466063 0.0))
((0 . "LINE") (100 . "AcDbEntity") (8 . "MASONRY") (62 . 7) (370 . 13) (100 . "AcDbLine") (10 12726.2443438914
2111.6141063348 0.0) (11 12726.2443438914 2088.9896719457 0.0))
((0 . "LINE") (100 . "AcDbEntity") (8 . "MASONRY") (62 . 7) (370 . 13) (100 . "AcDbLine") (10 12726.2443438914
2088.9896719457 0.0) (11 12560.3322850679 2088.9896719457 0.0))
((0 . "LINE") (100 . "AcDbEntity") (8 . "MASONRY") (62 . 7) (370 . 13) (100 . "AcDbLine") (10 12567.8733031674
2383.1073190045 0.0) (11 12730.0155429864 2383.1073190045 0.0))
((0 . "LINE") (100 . "AcDbEntity") (8 . "MASONRY") (62 . 7) (370 . 13) (100 . "AcDbLine") (10 12579.185520362
1436.6515837104 0.0) (11 12579.185520362 1447.963800905 0.0))
((0 . "LINE") (100 . "AcDbEntity") (8 . "MASONRY") (62 . 7) (370 . 13) (100 . "AcDbLine") (10 12971.3419230769
1436.6515837104 0.0) (11 12914.7808371041 1436.6515837104 0.0))
((0 . "LINE") (100 . "AcDbEntity") (8 . "MASONRY") (62 . 7) (370 . 13) (100 . "AcDbLine") (10 12914.7808371041
1436.6515837104 0.0) (11 12892.1508823529 1436.6515837104 0.0))
((0 . "LINE") (100 . "AcDbEntity") (8 . "MASONRY") (62 . 7) (370 . 13) (100 . "AcDbLine") (10 12892.1508823529
1436.6515837104 0.0) (11 12654.599841629 1436.6515837104 0.0))
((0 . "LINE") (100 . "AcDbEntity") (8 . "MASONRY") (62 . 7) (370 . 13) (100 . "AcDbLine") (10 12654.599841629
1436.6515837104 0.0) (11 12605.5811538462 1436.6515837104 0.0))
((0 . "LINE") (100 . "AcDbEntity") (8 . "MASONRY") (62 . 7) (370 . 13) (100 . "AcDbLine") (10 12605.5811538462
1436.6515837104 0.0) (11 12579.185520362 1436.6515837104 0.0))
((0 . "LINE") (100 . "AcDbEntity") (8 . "MASONRY") (62 . 7) (370 . 13) (100 . "AcDbLine") (10 12582.956719457
1134.9915384615 0.0) (11 12820.513280543 1134.9915384615 0.0))
((0 . "LINE") (100 . "AcDbEntity") (8 . "MASONRY") (62 . 7) (370 . 13) (100 . "AcDbLine") (10 12588.6114479638
1523.3795022624 0.0) (11 12588.6114479638 1534.691719457 0.0))
((0 . "LINE") (100 . "AcDbEntity") (8 . "MASONRY") (62 . 7) (370 . 13) (100 . "AcDbLine") (10 12590.4977375566
2039.9696040724 0.0) (11 12626.320678733 2039.9696040724 0.0))
((0 . "LINE") (100 . "AcDbEntity") (8 . "MASONRY") (62 . 7) (370 . 13) (100 . "AcDbLine") (10 12683.7102941176
833.5600339367 0.0) (11 12683.7102941176 723.9819004525 0.0))
((0 . "LINE") (100 . "AcDbEntity") (8 . "MASONRY") (62 . 7) (370 . 13) (100 . "AcDbLine") (10 12683.7102941176
723.9819004525 0.0) (11 12683.7102941176 607.2431900452 0.0))
((0 . "LINE") (100 . "AcDbEntity") (8 . "MASONRY") (62 . 7) (370 . 13) (100 . "AcDbLine") (10 12590.4977375566
845.4114819005 0.0) (11 12590.4977375566 863.4983257919 0.0))
((0 . "LINE") (100 . "AcDbEntity") (8 . "MASONRY") (62 . 7) (370 . 13) (100 . "AcDbLine") (10 12590.4977375566
868.9825113122 0.0) (11 12590.4977375566 863.4983257919 0.0))
((0 . "LINE") (100 . "AcDbEntity") (8 . "MASONRY") (62 . 7) (370 . 13) (100 . "AcDbLine") (10 12624.4343891403
1862.7453280543 0.0) (11 12616.8933710407 1862.7453280543 0.0))
((0 . "LINE") (100 . "AcDbEntity") (8 . "MASONRY") (62 . 7) (370 . 13) (100 . "AcDbLine") (10 13026.0180995475
1817.4971493213 0.0) (11 12624.4343891403 1817.4971493213 0.0))
((0 . "LINE") (100 . "AcDbEntity") (8 . "MASONRY") (62 . 7) (370 . 13) (100 . "AcDbLine") (10 12624.4343891403
1817.4971493213 0.0) (11 12624.4343891403 1798.6425339367 0.0))
((0 . "LINE") (100 . "AcDbEntity") (8 . "MASONRY") (62 . 7) (370 . 13) (100 . "AcDbLine") (10 12679.1105656109
2209.6528619909 0.0) (11 12628.2042081448 2209.6528619909 0.0))
((0 . "LINE") (100 . "AcDbEntity") (8 . "MASONRY") (62 . 7) (370 . 13) (100 . "AcDbLine") (10 12628.2042081448
2209.6528619909 0.0) (11 12628.2042081448 2243.5895135747 0.0))
((0 . "LINE") (100 . "AcDbEntity") (8 . "MASONRY") (62 . 7) (370 . 13) (100 . "AcDbLine") (10 12626.320678733
2039.9696040724 0.0) (11 12626.320678733 1975.8675 0.0))
((0 . "LINE") (100 . "AcDbEntity") (8 . "MASONRY") (62 . 7) (370 . 13) (100 . "AcDbLine") (10 12809.2010633484
2039.9696040724 0.0) (11 12626.320678733 2039.9696040724 0.0))
((0 . "LINE") (100 . "AcDbEntity") (8 . "MASONRY") (62 . 7) (370 . 13) (100 . "AcDbLine") (10 12677.2242760181
1184.0129864253 0.0) (11 12624.4343891403 1184.0129864253 0.0))
((0 . "LINE") (100 . "AcDbEntity") (8 . "MASONRY") (62 . 7) (370 . 13) (100 . "AcDbLine") (10 12628.2055882353
1941.9308484163 0.0) (11 12628.2055882353 1926.8474321267 0.0))
((0 . "LINE") (100 . "AcDbEntity") (8 . "MASONRY") (62 . 7) (370 . 13) (100 . "AcDbLine") (10 12839.3665158371
1926.8474321267 0.0) (11 12628.2055882353 1926.8474321267 0.0))
((0 . "LINE") (100 . "AcDbEntity") (8 . "MASONRY") (62 . 7) (370 . 13) (100 . "AcDbLine") (10 12631.9754072398
1263.1985067873 0.0) (11 12662.142239819 1263.1985067873 0.0))
((0 . "LINE") (100 . "AcDbEntity") (8 . "MASONRY") (62 . 7) (370 . 13) (100 . "AcDbLine") (10 12639.5178054299
1052.036199095 0.0) (11 12639.5178054299 1059.5785972851 0.0))
((0 . "LINE") (100 . "AcDbEntity") (8 . "MASONRY") (62 . 7) (370 . 13) (100 . "AcDbLine") (10 12639.5178054299
1052.036199095 0.0) (11 12807.3161538462 1052.036199095 0.0))
((0 . "LINE") (100 . "AcDbEntity") (8 . "MASONRY") (62 . 7) (370 . 13) (100 . "AcDbLine") (10 12750.83239819
912.5197737557 0.0) (11 12643.2876244344 912.5197737557 0.0))
((0 . "LINE") (100 . "AcDbEntity") (8 . "MASONRY") (62 . 7) (370 . 13) (100 . "AcDbLine") (10 12673.4544570136
3438.9140271493 0.0) (11 12665.9120588235 3438.9140271493 0.0))
((0 . "LINE") (100 . "AcDbEntity") (8 . "MASONRY") (62 . 7) (370 . 13) (100 . "AcDbLine") (10 12679.1105656109
2209.6528619909 0.0) (11 12737.556561086 2209.6528619909 0.0))
((0 . "LINE") (100 . "AcDbEntity") (8 . "MASONRY") (62 . 7) (370 . 13) (100 . "AcDbLine") (10 12737.556561086
2209.6528619909 0.0) (11 12895.92760181 2209.6528619909 0.0))
((0 . "LINE") (100 . "AcDbEntity") (8 . "MASONRY") (62 . 7) (370 . 13) (100 . "AcDbLine") (10 12679.1105656109
2209.6528619909 0.0) (11 12679.1105656109 2250.976561086 0.0))
((0 . "LINE") (100 . "AcDbEntity") (8 . "MASONRY") (62 . 7) (370 . 13) (100 . "AcDbLine") (10 12679.1105656109
2250.976561086 0.0) (11 12771.4932126697 2250.976561086 0.0))
((0 . "LINE") (100 . "AcDbEntity") (8 . "MASONRY") (62 . 7) (370 . 13) (100 . "AcDbLine") (10 12771.4932126697
2250.976561086 0.0) (11 12907.394479638 2250.976561086 0.0))
((0 . "LINE") (100 . "AcDbEntity") (8 . "MASONRY") (62 . 7) (370 . 13) (100 . "AcDbLine") (10 12692.3076923077
1423.4544570136 0.0) (11 12673.4544570136 1423.4544570136 0.0))
((0 . "LINE") (100 . "AcDbEntity") (8 . "MASONRY") (62 . 7) (370 . 13) (100 . "AcDbLine") (10 12673.4544570136
880.4680316742 0.0) (11 12707.3911085973 880.4680316742 0.0))
((0 . "LINE") (100 . "AcDbEntity") (8 . "MASONRY") (62 . 7) (370 . 13) (100 . "AcDbLine") (10 12726.2443438914
995.4751131222 0.0) (11 12688.5364932127 995.4751131222 0.0))
((0 . "LINE") (100 . "AcDbEntity") (8 . "MASONRY") (62 . 7) (370 . 13) (100 . "AcDbLine") (10 12707.3911085973
1415.9873190045 0.0) (11 12724.3594343891 1415.9873190045 0.0))
((0 . "LINE") (100 . "AcDbEntity") (8 . "MASONRY") (62 . 7) (370 . 13) (100 . "AcDbLine") (10 12714.9321266968
1242.4589819005 0.0) (11 12714.9321266968 1300.9049773756 0.0))
((0 . "LINE") (100 . "AcDbEntity") (8 . "MASONRY") (62 . 7) (370 . 13) (100 . "AcDbLine") (10 12707.3911085973
825.7918552036 0.0) (11 12824.2830995475 825.7918552036 0.0))
((0 . "LINE") (100 . "AcDbEntity") (8 . "MASONRY") (62 . 7) (370 . 13) (100 . "AcDbLine") (10 13114.6309276018
1104.8274660633 0.0) (11 12874.5003959276 1104.8274660633 0.0))
((0 . "LINE") (100 . "AcDbEntity") (8 . "MASONRY") (62 . 7) (370 . 13) (100 . "AcDbLine") (10 12874.5003959276
1104.8274660633 0.0) (11 12874.5003959276 1131.221719457 0.0))
((0 . "LINE") (100 . "AcDbEntity") (8 . "MASONRY") (62 . 7) (370 . 13) (100 . "AcDbLine") (10 12874.5003959276
1131.221719457 0.0) (11 12874.5003959276 1187.1807352941 0.0))
((0 . "LINE") (100 . "AcDbEntity") (8 . "MASONRY") (62 . 7) (370 . 13) (100 . "AcDbLine") (10 12874.5003959276
1187.1807352941 0.0) (11 12711.1609276018 1187.1807352941 0.0))
((0 . "LINE") (100 . "AcDbEntity") (8 . "MASONRY") (62 . 7) (370 . 13) (100 . "AcDbLine") (10 12724.3594343891
1387.6328959276 0.0) (11 12724.3594343891 1415.9873190045 0.0))
((0 . "LINE") (100 . "AcDbEntity") (8 . "MASONRY") (62 . 7) (370 . 13) (100 . "AcDbLine") (10 13088.2352941176
1344.2689366516 0.0) (11 12718.7033257919 1344.2689366516 0.0))
((0 . "LINE") (100 . "AcDbEntity") (8 . "MASONRY") (62 . 7) (370 . 13) (100 . "AcDbLine") (10 12718.7033257919
1344.2689366516 0.0) (11 12718.7033257919 1331.0718099548 0.0))
((0 . "LINE") (100 . "AcDbEntity") (8 . "MASONRY") (62 . 7) (370 . 13) (100 . "AcDbLine") (10 12726.2443438914
2111.6141063348 0.0) (11 12726.2443438914 2130.467341629 0.0))
((0 . "LINE") (100 . "AcDbEntity") (8 . "MASONRY") (62 . 7) (370 . 13) (100 . "AcDbLine") (10 13012.8209728507
2111.6141063348 0.0) (11 12726.2443438914 2111.6141063348 0.0))
((0 . "LINE") (100 . "AcDbEntity") (8 . "MASONRY") (62 . 7) (370 . 13) (100 . "AcDbLine") (10 12724.3594343891
1415.9873190045 0.0) (11 12839.3665158371 1415.9873190045 0.0))
((0 . "LINE") (100 . "AcDbEntity") (8 . "MASONRY") (62 . 7) (370 . 13) (100 . "AcDbLine") (10 12839.3665158371
1415.9873190045 0.0) (11 12858.2197511312 1415.9873190045 0.0))
((0 . "LINE") (100 . "AcDbEntity") (8 . "MASONRY") (62 . 7) (370 . 13) (100 . "AcDbLine") (10 12737.559321267
1711.9146153846 0.0) (11 12737.559321267 1681.8271832579 0.0))
((0 . "LINE") (100 . "AcDbEntity") (8 . "MASONRY") (62 . 7) (370 . 13) (100 . "AcDbLine") (10 12737.559321267
1681.8271832579 0.0) (11 12850.6787330317 1681.8271832579 0.0))
((0 . "LINE") (100 . "AcDbEntity") (8 . "MASONRY") (62 . 7) (370 . 13) (100 . "AcDbLine") (10 12756.4097963801
2496.2294909502 0.0) (11 12745.0975791855 2496.2294909502 0.0))
((0 . "LINE") (100 . "AcDbEntity") (8 . "MASONRY") (62 . 7) (370 . 13) (100 . "AcDbLine") (10 12786.5766289593
886.122760181 0.0) (11 12750.83239819 886.122760181 0.0))
((0 . "LINE") (100 . "AcDbEntity") (8 . "MASONRY") (62 . 7) (370 . 13) (100 . "AcDbLine") (10 12750.83239819
886.122760181 0.0) (11 12750.83239819 912.5197737557 0.0))
((0 . "LINE") (100 . "AcDbEntity") (8 . "MASONRY") (62 . 7) (370 . 13) (100 . "AcDbLine") (10 12774.662341629
969.0808597285 0.0) (11 12774.662341629 912.5197737557 0.0))
((0 . "LINE") (100 . "AcDbEntity") (8 . "MASONRY") (62 . 7) (370 . 13) (100 . "AcDbLine") (10 12774.662341629
912.5197737557 0.0) (11 12750.83239819 912.5197737557 0.0))
((0 . "LINE") (100 . "AcDbEntity") (8 . "MASONRY") (62 . 7) (370 . 13) (100 . "AcDbLine") (10 12752.6399773756
1263.1985067873 0.0) (11 12854.4499321267 1263.1985067873 0.0))
((0 . "LINE") (100 . "AcDbEntity") (8 . "MASONRY") (62 . 7) (370 . 13) (100 . "AcDbLine") (10 12756.4097963801
2379.3368099548 0.0) (11 12779.0342307692 2379.3368099548 0.0))
((0 . "LINE") (100 . "AcDbEntity") (8 . "MASONRY") (62 . 7) (370 . 13) (100 . "AcDbLine") (10 12756.4097963801
995.4751131222 0.0) (11 13029.787918552 995.4751131222 0.0))
((0 . "LINE") (100 . "AcDbEntity") (8 . "MASONRY") (62 . 7) (370 . 13) (100 . "AcDbLine") (10 12905.4860972851
711.8625565611 0.0) (11 12905.4860972851 796.9085520362 0.0))
((0 . "LINE") (100 . "AcDbEntity") (8 . "MASONRY") (62 . 7) (370 . 13) (100 . "AcDbLine") (10 12905.4860972851
796.9085520362 0.0) (11 12821.6939366516 796.9085520362 0.0))
((0 . "LINE") (100 . "AcDbEntity") (8 . "MASONRY") (62 . 7) (370 . 13) (100 . "AcDbLine") (10 12821.6939366516
796.9085520362 0.0) (11 12821.6939366516 659.0119117647 0.0))
((0 . "LINE") (100 . "AcDbEntity") (8 . "MASONRY") (62 . 7) (370 . 13) (100 . "AcDbLine") (10 12763.9521945701
2319.0045248869 0.0) (11 12763.9521945701 2345.3994683258 0.0))
((0 . "LINE") (100 . "AcDbEntity") (8 . "MASONRY") (62 . 7) (370 . 13) (100 . "AcDbLine") (10 12763.9521945701
2303.9217986425 0.0) (11 12763.9521945701 2319.0045248869 0.0))
((0 . "LINE") (100 . "AcDbEntity") (8 . "MASONRY") (62 . 7) (370 . 13) (100 . "AcDbLine") (10 12771.4932126697 2500 0.0)
(11 12914.7808371041 2500 0.0))
((0 . "LINE") (100 . "AcDbEntity") (8 . "MASONRY") (62 . 7) (370 . 13) (100 . "AcDbLine") (10 12912.8959276018
2319.0045248869 0.0) (11 12877.0743665158 2319.0045248869 0.0))
((0 . "LINE") (100 . "AcDbEntity") (8 . "MASONRY") (62 . 7) (370 . 13) (100 . "AcDbLine") (10 12877.0743665158
2319.0045248869 0.0) (11 12763.9521945701 2319.0045248869 0.0))
((0 . "LINE") (100 . "AcDbEntity") (8 . "MASONRY") (62 . 7) (370 . 13) (100 . "AcDbLine") (10 12779.0342307692
3423.8306108597 0.0) (11 12831.8254977376 3423.8306108597 0.0))
((0 . "LINE") (100 . "AcDbEntity") (8 . "MASONRY") (62 . 7) (370 . 13) (100 . "AcDbLine") (10 12779.0342307692
3386.1234502262 0.0) (11 12779.0342307692 3306.9379298643 0.0))
((0 . "LINE") (100 . "AcDbEntity") (8 . "MASONRY") (62 . 7) (370 . 13) (100 . "AcDbLine") (10 12784.6903393665
3186.274739819 0.0) (11 12784.6903393665 3205.1279751131 0.0))
((0 . "LINE") (100 . "AcDbEntity") (8 . "MASONRY") (62 . 7) (370 . 13) (100 . "AcDbLine") (10 12877.0702262443
3118.4014366516 0.0) (11 12877.0702262443 3131.5219230769 0.0))
((0 . "LINE") (100 . "AcDbEntity") (8 . "MASONRY") (62 . 7) (370 . 13) (100 . "AcDbLine") (10 12877.0702262443
3131.5219230769 0.0) (11 12779.0342307692 3131.5219230769 0.0))
((0 . "LINE") (100 . "AcDbEntity") (8 . "MASONRY") (62 . 7) (370 . 13) (100 . "AcDbLine") (10 12816.5570475113
3039.2159162896 0.0) (11 12816.5570475113 3048.4581900452 0.0))
((0 . "LINE") (100 . "AcDbEntity") (8 . "MASONRY") (62 . 7) (370 . 13) (100 . "AcDbLine") (10 12816.5570475113
3048.4581900452 0.0) (11 12779.0342307692 3048.4581900452 0.0))
((0 . "LINE") (100 . "AcDbEntity") (8 . "MASONRY") (62 . 7) (370 . 13) (100 . "AcDbLine") (10 13054.2986425339
2733.7860520362 0.0) (11 12779.0342307692 2733.7860520362 0.0))
((0 . "LINE") (100 . "AcDbEntity") (8 . "MASONRY") (62 . 7) (370 . 13) (100 . "AcDbLine") (10 12788.4615384615
3269.2307692308 0.0) (11 12788.4615384615 3254.3027036199 0.0))
((0 . "LINE") (100 . "AcDbEntity") (8 . "MASONRY") (62 . 7) (370 . 13) (100 . "AcDbLine") (10 12788.4615384615
3254.3027036199 0.0) (11 13001.5087556561 3254.3027036199 0.0))
((0 . "LINE") (100 . "AcDbEntity") (8 . "MASONRY") (62 . 7) (370 . 13) (100 . "AcDbLine") (10 12811.0859728507
2990.1958484163 0.0) (11 12782.8054298643 2990.1958484163 0.0))
((0 . "LINE") (100 . "AcDbEntity") (8 . "MASONRY") (62 . 7) (370 . 13) (100 . "AcDbLine") (10 12820.513280543
2895.92760181 0.0) (11 12782.8054298643 2895.92760181 0.0))
((0 . "LINE") (100 . "AcDbEntity") (8 . "MASONRY") (62 . 7) (370 . 13) (100 . "AcDbLine") (10 13034.8433371041
2635.7466063348 0.0) (11 12782.8054298643 2635.7466063348 0.0))
((0 . "LINE") (100 . "AcDbEntity") (8 . "MASONRY") (62 . 7) (370 . 13) (100 . "AcDbLine") (10 12786.5766289593
2579.185520362 0.0) (11 12861.9909502262 2579.185520362 0.0))
((0 . "LINE") (100 . "AcDbEntity") (8 . "MASONRY") (62 . 7) (370 . 13) (100 . "AcDbLine") (10 12861.9909502262
2579.185520362 0.0) (11 12990.1965384615 2579.185520362 0.0))
((0 . "LINE") (100 . "AcDbEntity") (8 . "MASONRY") (62 . 7) (370 . 13) (100 . "AcDbLine") (10 12786.5766289593
886.122760181 0.0) (11 12786.5766289593 855.9586877828 0.0))
((0 . "LINE") (100 . "AcDbEntity") (8 . "MASONRY") (62 . 7) (370 . 13) (100 . "AcDbLine") (10 12786.5766289593
886.122760181 0.0) (11 12794.1176470588 886.122760181 0.0))
((0 . "LINE") (100 . "AcDbEntity") (8 . "MASONRY") (62 . 7) (370 . 13) (100 . "AcDbLine") (10 12807.3161538462
1025.6419457014 0.0) (11 12807.3161538462 1052.036199095 0.0))
((0 . "LINE") (100 . "AcDbEntity") (8 . "MASONRY") (62 . 7) (370 . 13) (100 . "AcDbLine") (10 12839.3665158371
2990.1958484163 0.0) (11 12811.0859728507 2990.1958484163 0.0))
((0 . "LINE") (100 . "AcDbEntity") (8 . "MASONRY") (62 . 7) (370 . 13) (100 . "AcDbLine") (10 12811.0859728507
3001.5080656109 0.0) (11 12811.0859728507 2990.1958484163 0.0))
((0 . "LINE") (100 . "AcDbEntity") (8 . "MASONRY") (62 . 7) (370 . 13) (100 . "AcDbLine") (10 12807.3161538462
1052.036199095 0.0) (11 13042.9864253394 1052.036199095 0.0))
((0 . "LINE") (100 . "AcDbEntity") (8 . "MASONRY") (62 . 7) (370 . 13) (100 . "AcDbLine") (10 12820.513280543
2895.92760181 0.0) (11 12820.513280543 2926.0937443439 0.0))
((0 . "LINE") (100 . "AcDbEntity") (8 . "MASONRY") (62 . 7) (370 . 13) (100 . "AcDbLine") (10 13156.1085972851
2895.92760181 0.0) (11 12820.513280543 2895.92760181 0.0))
((0 . "LINE") (100 . "AcDbEntity") (8 . "MASONRY") (62 . 7) (370 . 13) (100 . "AcDbLine") (10 12820.513280543
2375.5656108597 0.0) (11 12854.4499321267 2375.5656108597 0.0))
((0 . "LINE") (100 . "AcDbEntity") (8 . "MASONRY") (62 . 7) (370 . 13) (100 . "AcDbLine") (10 12820.513280543
1112.3671040724 0.0) (11 12820.513280543 1097.2850678733 0.0))
((0 . "LINE") (100 . "AcDbEntity") (8 . "MASONRY") (62 . 7) (370 . 13) (100 . "AcDbLine") (10 12824.2830995475
2041.8552036199 0.0) (11 12861.9909502262 2041.8552036199 0.0))
((0 . "LINE") (100 . "AcDbEntity") (8 . "MASONRY") (62 . 7) (370 . 13) (100 . "AcDbLine") (10 12841.2528054299
3190.0452488688 0.0) (11 12841.2528054299 3182.503540724 0.0))
((0 . "LINE") (100 . "AcDbEntity") (8 . "MASONRY") (62 . 7) (370 . 13) (100 . "AcDbLine") (10 12850.6787330317
1240.5740723982 0.0) (11 12839.3665158371 1240.5740723982 0.0))
((0 . "LINE") (100 . "AcDbEntity") (8 . "MASONRY") (62 . 7) (370 . 13) (100 . "AcDbLine") (10 12899.698800905
1681.8271832579 0.0) (11 12850.6787330317 1681.8271832579 0.0))
((0 . "LINE") (100 . "AcDbEntity") (8 . "MASONRY") (62 . 7) (370 . 13) (100 . "AcDbLine") (10 12850.6787330317
1681.8271832579 0.0) (11 12850.6787330317 1730.7692307692 0.0))
((0 . "LINE") (100 . "AcDbEntity") (8 . "MASONRY") (62 . 7) (370 . 13) (100 . "AcDbLine") (10 12858.2197511312
1926.8474321267 0.0) (11 12888.3865837104 1926.8474321267 0.0))
((0 . "LINE") (100 . "AcDbEntity") (8 . "MASONRY") (62 . 7) (370 . 13) (100 . "AcDbLine") (10 12883.5824773756
509.6663348416 0.0) (11 12883.5824773756 606.1875 0.0))
((0 . "LINE") (100 . "AcDbEntity") (8 . "MASONRY") (62 . 7) (370 . 13) (100 . "AcDbLine") (10 12883.5824773756 606.1875
0.0) (11 12952.4886877828 606.1875 0.0))
((0 . "LINE") (100 . "AcDbEntity") (8 . "MASONRY") (62 . 7) (370 . 13) (100 . "AcDbLine") (10 12952.4886877828 606.1875
0.0) (11 13035.4454072398 606.1875 0.0))
((0 . "LINE") (100 . "AcDbEntity") (8 . "MASONRY") (62 . 7) (370 . 13) (100 . "AcDbLine") (10 13035.4454072398 606.1875
0.0) (11 13061.6919004525 606.1875 0.0))
((0 . "LINE") (100 . "AcDbEntity") (8 . "MASONRY") (62 . 7) (370 . 13) (100 . "AcDbLine") (10 13061.6919004525 606.1875
0.0) (11 13061.6919004525 595.7776923077 0.0))
((0 . "LINE") (100 . "AcDbEntity") (8 . "MASONRY") (62 . 7) (370 . 13) (100 . "AcDbLine") (10 13061.6919004525
595.7776923077 0.0) (11 13061.6919004525 497.7375565611 0.0))
((0 . "LINE") (100 . "AcDbEntity") (8 . "MASONRY") (62 . 7) (370 . 13) (100 . "AcDbLine") (10 12960.0297058824
3399.3985972851 0.0) (11 12873.3031674208 3399.3985972851 0.0))
((0 . "LINE") (100 . "AcDbEntity") (8 . "MASONRY") (62 . 7) (370 . 13) (100 . "AcDbLine") (10 12873.3031674208
3399.3985972851 0.0) (11 12873.3031674208 3420.06010181 0.0))
((0 . "LINE") (100 . "AcDbEntity") (8 . "MASONRY") (62 . 7) (370 . 13) (100 . "AcDbLine") (10 12865.7621493213
2982.6548303167 0.0) (11 13076.9230769231 2982.6548303167 0.0))
((0 . "LINE") (100 . "AcDbEntity") (8 . "MASONRY") (62 . 7) (370 . 13) (100 . "AcDbLine") (10 13005.2785746606
535.4454072398 0.0) (11 12910.3716628959 535.4454072398 0.0))
((0 . "LINE") (100 . "AcDbEntity") (8 . "MASONRY") (62 . 7) (370 . 13) (100 . "AcDbLine") (10 12886.5016742081
3182.503540724 0.0) (11 12877.0743665158 3182.503540724 0.0))
((0 . "LINE") (100 . "AcDbEntity") (8 . "MASONRY") (62 . 7) (370 . 13) (100 . "AcDbLine") (10 12878.9592760181
2850.6787330317 0.0) (11 12878.9592760181 2831.8248076923 0.0))
((0 . "LINE") (100 . "AcDbEntity") (8 . "MASONRY") (62 . 7) (370 . 13) (100 . "AcDbLine") (10 12888.3865837104
3082.5791855204 0.0) (11 12880.8441855204 3082.5791855204 0.0))
((0 . "LINE") (100 . "AcDbEntity") (8 . "MASONRY") (62 . 7) (370 . 13) (100 . "AcDbLine") (10 12886.5016742081
3182.503540724 0.0) (11 12886.5016742081 3156.1085972851 0.0))
((0 . "LINE") (100 . "AcDbEntity") (8 . "MASONRY") (62 . 7) (370 . 13) (100 . "AcDbLine") (10 12886.5016742081
3182.503540724 0.0) (11 12895.92760181 3182.503540724 0.0))
((0 . "LINE") (100 . "AcDbEntity") (8 . "MASONRY") (62 . 7) (370 . 13) (100 . "AcDbLine") (10 12903.4686199095
1278.2805429864 0.0) (11 12884.6153846154 1278.2805429864 0.0))
((0 . "LINE") (100 . "AcDbEntity") (8 . "MASONRY") (62 . 7) (370 . 13) (100 . "AcDbLine") (10 12888.3865837104
1953.2430656109 0.0) (11 12888.3865837104 1926.8474321267 0.0))
((0 . "LINE") (100 . "AcDbEntity") (8 . "MASONRY") (62 . 7) (370 . 13) (100 . "AcDbLine") (10 13114.6309276018
1926.8474321267 0.0) (11 12888.3865837104 1926.8474321267 0.0))
((0 . "LINE") (100 . "AcDbEntity") (8 . "MASONRY") (62 . 7) (370 . 13) (100 . "AcDbLine") (10 12892.7598529412
1572.3981900452 0.0) (11 12892.7598529412 1508.2988461538 0.0))
((0 . "LINE") (100 . "AcDbEntity") (8 . "MASONRY") (62 . 7) (370 . 13) (100 . "AcDbLine") (10 12892.7598529412
1508.2988461538 0.0) (11 12929.8642533937 1508.2988461538 0.0))
((0 . "LINE") (100 . "AcDbEntity") (8 . "MASONRY") (62 . 7) (370 . 13) (100 . "AcDbLine") (10 12967.5721040724
888.0090497738 0.0) (11 12888.3865837104 888.0090497738 0.0))
((0 . "LINE") (100 . "AcDbEntity") (8 . "MASONRY") (62 . 7) (370 . 13) (100 . "AcDbLine") (10 12892.1564027149
2039.9702941176 0.0) (11 12903.4686199095 2039.9702941176 0.0))
((0 . "LINE") (100 . "AcDbEntity") (8 . "MASONRY") (62 . 7) (370 . 13) (100 . "AcDbLine") (10 12892.1564027149
2002.2624434389 0.0) (11 12892.1564027149 1994.7207352941 0.0))
((0 . "LINE") (100 . "AcDbEntity") (8 . "MASONRY") (62 . 7) (370 . 13) (100 . "AcDbLine") (10 12895.92760181
2373.6807013575 0.0) (11 12907.2398190045 2373.6807013575 0.0))
((0 . "LINE") (100 . "AcDbEntity") (8 . "MASONRY") (62 . 7) (370 . 13) (100 . "AcDbLine") (10 12899.698800905
1681.8271832579 0.0) (11 13039.2152262443 1681.8271832579 0.0))
((0 . "LINE") (100 . "AcDbEntity") (8 . "MASONRY") (62 . 7) (370 . 13) (100 . "AcDbLine") (10 12899.698800905
1681.8271832579 0.0) (11 12899.698800905 1647.8138914027 0.0))
((0 . "LINE") (100 . "AcDbEntity") (8 . "MASONRY") (62 . 7) (370 . 13) (100 . "AcDbLine") (10 12907.2398190045
2356.7116855204 0.0) (11 12907.2398190045 2373.6807013575 0.0))
((0 . "LINE") (100 . "AcDbEntity") (8 . "MASONRY") (62 . 7) (370 . 13) (100 . "AcDbLine") (10 12907.2398190045
2373.6807013575 0.0) (11 12907.2398190045 2390.6483371041 0.0))
((0 . "LINE") (100 . "AcDbEntity") (8 . "MASONRY") (62 . 7) (370 . 13) (100 . "AcDbLine") (10 13133.4841628959
2227.2239479638 0.0) (11 12907.394479638 2227.2239479638 0.0))
((0 . "LINE") (100 . "AcDbEntity") (8 . "MASONRY") (62 . 7) (370 . 13) (100 . "AcDbLine") (10 12907.394479638
2227.2239479638 0.0) (11 12907.394479638 2250.976561086 0.0))
((0 . "LINE") (100 . "AcDbEntity") (8 . "MASONRY") (62 . 7) (370 . 13) (100 . "AcDbLine") (10 12907.394479638
2258.6729298643 0.0) (11 12907.394479638 2250.976561086 0.0))
((0 . "LINE") (100 . "AcDbEntity") (8 . "MASONRY") (62 . 7) (370 . 13) (100 . "AcDbLine") (10 12912.8959276018
2288.8383823529 0.0) (11 12912.8959276018 2319.0045248869 0.0))
((0 . "LINE") (100 . "AcDbEntity") (8 . "MASONRY") (62 . 7) (370 . 13) (100 . "AcDbLine") (10 12914.7808371041
2450.9806221719 0.0) (11 12914.7808371041 2500 0.0))
((0 . "LINE") (100 . "AcDbEntity") (8 . "MASONRY") (62 . 7) (370 . 13) (100 . "AcDbLine") (10 12914.7808371041 2500 0.0)
(11 13035.4454072398 2500 0.0))
((0 . "LINE") (100 . "AcDbEntity") (8 . "MASONRY") (62 . 7) (370 . 13) (100 . "AcDbLine") (10 13035.4454072398 2500 0.0)
(11 13035.4454072398 2526.3949434389 0.0))
((0 . "LINE") (100 . "AcDbEntity") (8 . "MASONRY") (62 . 7) (370 . 13) (100 . "AcDbLine") (10 12914.7808371041
2450.9806221719 0.0) (11 12914.7808371041 2413.2727714932 0.0))
((0 . "LINE") (100 . "AcDbEntity") (8 . "MASONRY") (62 . 7) (370 . 13) (100 . "AcDbLine") (10 13137.255361991
2319.0045248869 0.0) (11 12912.8959276018 2319.0045248869 0.0))
((0 . "LINE") (100 . "AcDbEntity") (8 . "MASONRY") (62 . 7) (370 . 13) (100 . "AcDbLine") (10 13024.1331900452
2450.9806221719 0.0) (11 12914.7808371041 2450.9806221719 0.0))
((0 . "LINE") (100 . "AcDbEntity") (8 . "MASONRY") (62 . 7) (370 . 13) (100 . "AcDbLine") (10 12929.8642533937
3188.1603393665 0.0) (11 12967.5721040724 3188.1603393665 0.0))
((0 . "LINE") (100 . "AcDbEntity") (8 . "MASONRY") (62 . 7) (370 . 13) (100 . "AcDbLine") (10 13118.4007466063
2198.3413348416 0.0) (11 12929.8642533937 2198.3413348416 0.0))
((0 . "LINE") (100 . "AcDbEntity") (8 . "MASONRY") (62 . 7) (370 . 13) (100 . "AcDbLine") (10 12967.5721040724
3150.4524886878 0.0) (11 12937.4052714932 3150.4524886878 0.0))
((0 . "LINE") (100 . "AcDbEntity") (8 . "MASONRY") (62 . 7) (370 . 13) (100 . "AcDbLine") (10 13127.8280542986
3076.874061086 0.0) (11 12937.4052714932 3076.874061086 0.0))
((0 . "LINE") (100 . "AcDbEntity") (8 . "MASONRY") (62 . 7) (370 . 13) (100 . "AcDbLine") (10 12937.4052714932
1255.5014479638 0.0) (11 12963.8078054299 1255.5014479638 0.0))
((0 . "LINE") (100 . "AcDbEntity") (8 . "MASONRY") (62 . 7) (370 . 13) (100 . "AcDbLine") (10 12963.8078054299
1255.5014479638 0.0) (11 13058.069841629 1255.5014479638 0.0))
((0 . "LINE") (100 . "AcDbEntity") (8 . "MASONRY") (62 . 7) (370 . 13) (100 . "AcDbLine") (10 13016.5907918552
1506.4097963801 0.0) (11 12941.1764705882 1506.4097963801 0.0))
((0 . "LINE") (100 . "AcDbEntity") (8 . "MASONRY") (62 . 7) (370 . 13) (100 . "AcDbLine") (10 12956.2598868778
723.0401357466 0.0) (11 13269.2307692308 723.0401357466 0.0))
((0 . "LINE") (100 . "AcDbEntity") (8 . "MASONRY") (62 . 7) (370 . 13) (100 . "AcDbLine") (10 12982.6541402715
3408.5966742081 0.0) (11 12995.2491968326 3408.5966742081 0.0))
((0 . "LINE") (100 . "AcDbEntity") (8 . "MASONRY") (62 . 7) (370 . 13) (100 . "AcDbLine") (10 12995.2491968326
3408.5966742081 0.0) (11 12995.2491968326 3389.8946493213 0.0))
((0 . "LINE") (100 . "AcDbEntity") (8 . "MASONRY") (62 . 7) (370 . 13) (100 . "AcDbLine") (10 13012.8209728507
822.0220361991 0.0) (11 12982.6541402715 822.0220361991 0.0))
((0 . "LINE") (100 . "AcDbEntity") (8 . "MASONRY") (62 . 7) (370 . 13) (100 . "AcDbLine") (10 12997.7375565611
893.665158371 0.0) (11 13012.8209728507 893.665158371 0.0))
((0 . "LINE") (100 . "AcDbEntity") (8 . "MASONRY") (62 . 7) (370 . 13) (100 . "AcDbLine") (10 13031.6742081448
3342.7601809955 0.0) (11 13001.5087556561 3342.7601809955 0.0))
((0 . "LINE") (100 . "AcDbEntity") (8 . "MASONRY") (62 . 7) (370 . 13) (100 . "AcDbLine") (10 13001.5087556561
3254.3027036199 0.0) (11 13001.5087556561 3295.6257126697 0.0))
((0 . "LINE") (100 . "AcDbEntity") (8 . "MASONRY") (62 . 7) (370 . 13) (100 . "AcDbLine") (10 13001.5087556561
3254.3027036199 0.0) (11 13009.0497737557 3254.3027036199 0.0))
((0 . "LINE") (100 . "AcDbEntity") (8 . "MASONRY") (62 . 7) (370 . 13) (100 . "AcDbLine") (10 13012.8209728507
822.0220361991 0.0) (11 13012.8209728507 893.665158371 0.0))
((0 . "LINE") (100 . "AcDbEntity") (8 . "MASONRY") (62 . 7) (370 . 13) (100 . "AcDbLine") (10 13012.8209728507
893.665158371 0.0) (11 13012.8209728507 916.2895927602 0.0))
((0 . "LINE") (100 . "AcDbEntity") (8 . "MASONRY") (62 . 7) (370 . 13) (100 . "AcDbLine") (10 13012.8209728507
935.1442081448 0.0) (11 13012.8209728507 972.850678733 0.0))
((0 . "LINE") (100 . "AcDbEntity") (8 . "MASONRY") (62 . 7) (370 . 13) (100 . "AcDbLine") (10 13034.8433371041
2635.7466063348 0.0) (11 13034.8433371041 2581.0711199095 0.0))
((0 . "LINE") (100 . "AcDbEntity") (8 . "MASONRY") (62 . 7) (370 . 13) (100 . "AcDbLine") (10 13034.8433371041
2581.0711199095 0.0) (11 13016.5907918552 2581.0711199095 0.0))
((0 . "LINE") (100 . "AcDbEntity") (8 . "MASONRY") (62 . 7) (370 . 13) (100 . "AcDbLine") (10 13012.8209728507
822.0220361991 0.0) (11 13046.7576244344 822.0220361991 0.0))
((0 . "LINE") (100 . "AcDbEntity") (8 . "MASONRY") (62 . 7) (370 . 13) (100 . "AcDbLine") (10 13024.1331900452
2450.9806221719 0.0) (11 13024.1331900452 2462.2928393665 0.0))
((0 . "LINE") (100 . "AcDbEntity") (8 . "MASONRY") (62 . 7) (370 . 13) (100 . "AcDbLine") (10 13024.1331900452
2450.9806221719 0.0) (11 13024.1331900452 2406.7812217195 0.0))
((0 . "LINE") (100 . "AcDbEntity") (8 . "MASONRY") (62 . 7) (370 . 13) (100 . "AcDbLine") (10 13024.1331900452
2406.7812217195 0.0) (11 13367.2695248869 2406.7812217195 0.0))
((0 . "LINE") (100 . "AcDbEntity") (8 . "MASONRY") (62 . 7) (370 . 13) (100 . "AcDbLine") (10 13367.2695248869
2406.7812217195 0.0) (11 13380.2098076923 2406.7812217195 0.0))
((0 . "LINE") (100 . "AcDbEntity") (8 . "MASONRY") (62 . 7) (370 . 13) (100 . "AcDbLine") (10 13380.2098076923
2406.7812217195 0.0) (11 13380.2098076923 2424.5849886878 0.0))
((0 . "LINE") (100 . "AcDbEntity") (8 . "MASONRY") (62 . 7) (370 . 13) (100 . "AcDbLine") (10 13027.9043891403
1847.6619117647 0.0) (11 13027.9043891403 1870.2863461538 0.0))
((0 . "LINE") (100 . "AcDbEntity") (8 . "MASONRY") (62 . 7) (370 . 13) (100 . "AcDbLine") (10 13026.0180995475
1817.4971493213 0.0) (11 13026.0180995475 1760.9360633484 0.0))
((0 . "LINE") (100 . "AcDbEntity") (8 . "MASONRY") (62 . 7) (370 . 13) (100 . "AcDbLine") (10 13026.0180995475
1817.4971493213 0.0) (11 13163.6496153846 1817.4971493213 0.0))
((0 . "LINE") (100 . "AcDbEntity") (8 . "MASONRY") (62 . 7) (370 . 13) (100 . "AcDbLine") (10 13024.1331900452
1442.3076923077 0.0) (11 13314.4796380091 1442.3076923077 0.0))
((0 . "LINE") (100 . "AcDbEntity") (8 . "MASONRY") (62 . 7) (370 . 13) (100 . "AcDbLine") (10 13029.787918552
1021.8693665158 0.0) (11 13029.787918552 995.4751131222 0.0))
((0 . "LINE") (100 . "AcDbEntity") (8 . "MASONRY") (62 . 7) (370 . 13) (100 . "AcDbLine") (10 13190.0452488688
995.4751131222 0.0) (11 13029.787918552 995.4751131222 0.0))
((0 . "LINE") (100 . "AcDbEntity") (8 . "MASONRY") (62 . 7) (370 . 13) (100 . "AcDbLine") (10 13034.8433371041
2635.7466063348 0.0) (11 13125.9431447964 2635.7466063348 0.0))
((0 . "LINE") (100 . "AcDbEntity") (8 . "MASONRY") (62 . 7) (370 . 13) (100 . "AcDbLine") (10 13035.4454072398
2541.4783597285 0.0) (11 13035.4454072398 2526.3949434389 0.0))
((0 . "LINE") (100 . "AcDbEntity") (8 . "MASONRY") (62 . 7) (370 . 13) (100 . "AcDbLine") (10 13054.2986425339
2526.3949434389 0.0) (11 13035.4454072398 2526.3949434389 0.0))
((0 . "LINE") (100 . "AcDbEntity") (8 . "MASONRY") (62 . 7) (370 . 13) (100 . "AcDbLine") (10 13048.6425339367
2092.7601809955 0.0) (11 13048.6425339367 2111.6141063348 0.0))
((0 . "LINE") (100 . "AcDbEntity") (8 . "MASONRY") (62 . 7) (370 . 13) (100 . "AcDbLine") (10 13048.6425339367
2111.6141063348 0.0) (11 13310.708438914 2111.6141063348 0.0))
((0 . "LINE") (100 . "AcDbEntity") (8 . "MASONRY") (62 . 7) (370 . 13) (100 . "AcDbLine") (10 13118.4007466063
2026.7724773756 0.0) (11 13042.9864253394 2026.7724773756 0.0))
((0 . "LINE") (100 . "AcDbEntity") (8 . "MASONRY") (62 . 7) (370 . 13) (100 . "AcDbLine") (10 13107.0885294118
3337.1040723982 0.0) (11 13046.7576244344 3337.1040723982 0.0))
((0 . "LINE") (100 . "AcDbEntity") (8 . "MASONRY") (62 . 7) (370 . 13) (100 . "AcDbLine") (10 13054.2986425339
2714.9321266968 0.0) (11 13054.2986425339 2733.7860520362 0.0))
((0 . "LINE") (100 . "AcDbEntity") (8 . "MASONRY") (62 . 7) (370 . 13) (100 . "AcDbLine") (10 13129.7143438914
2733.7860520362 0.0) (11 13122.1719457014 2733.7860520362 0.0))
((0 . "LINE") (100 . "AcDbEntity") (8 . "MASONRY") (62 . 7) (370 . 13) (100 . "AcDbLine") (10 13122.1719457014
2733.7860520362 0.0) (11 13054.2986425339 2733.7860520362 0.0))
((0 . "LINE") (100 . "AcDbEntity") (8 . "MASONRY") (62 . 7) (370 . 13) (100 . "AcDbLine") (10 13061.841040724
1508.2947058824 0.0) (11 13061.841040724 1519.6069230769 0.0))
((0 . "LINE") (100 . "AcDbEntity") (8 . "MASONRY") (62 . 7) (370 . 13) (100 . "AcDbLine") (10 13076.9230769231
1255.5014479638 0.0) (11 13058.069841629 1255.5014479638 0.0))
((0 . "LINE") (100 . "AcDbEntity") (8 . "MASONRY") (62 . 7) (370 . 13) (100 . "AcDbLine") (10 13076.9230769231
1255.5014479638 0.0) (11 13124.0582352941 1255.5014479638 0.0))
((0 . "LINE") (100 . "AcDbEntity") (8 . "MASONRY") (62 . 7) (370 . 13) (100 . "AcDbLine") (10 13284.3128054299
2530.2434728507 0.0) (11 13276.7717873303 2530.2434728507 0.0))
((0 . "LINE") (100 . "AcDbEntity") (8 . "MASONRY") (62 . 7) (370 . 13) (100 . "AcDbLine") (10 13276.7717873303
2530.2434728507 0.0) (11 13065.6108597285 2530.2434728507 0.0))
((0 . "LINE") (100 . "AcDbEntity") (8 . "MASONRY") (62 . 7) (370 . 13) (100 . "AcDbLine") (10 13073.1560180995
2865.761459276 0.0) (11 13073.1560180995 2827.5295588235 0.0))
((0 . "LINE") (100 . "AcDbEntity") (8 . "MASONRY") (62 . 7) (370 . 13) (100 . "AcDbLine") (10 13073.1560180995
2827.5295588235 0.0) (11 13129.7129638009 2827.5295588235 0.0))
((0 . "LINE") (100 . "AcDbEntity") (8 . "MASONRY") (62 . 7) (370 . 13) (100 . "AcDbLine") (10 13129.7129638009
2827.5295588235 0.0) (11 13129.7129638009 2800.1859502262 0.0))
((0 . "LINE") (100 . "AcDbEntity") (8 . "MASONRY") (62 . 7) (370 . 13) (100 . "AcDbLine") (10 13156.1085972851
3186.2733597285 0.0) (11 13073.1518778281 3186.2733597285 0.0))
((0 . "LINE") (100 . "AcDbEntity") (8 . "MASONRY") (62 . 7) (370 . 13) (100 . "AcDbLine") (10 13280.5429864253
1553.6209049774 0.0) (11 13078.8079864253 1553.6209049774 0.0))
((0 . "LINE") (100 . "AcDbEntity") (8 . "MASONRY") (62 . 7) (370 . 13) (100 . "AcDbLine") (10 13078.8079864253
1553.6209049774 0.0) (11 13078.8079864253 1579.9405882353 0.0))
((0 . "LINE") (100 . "AcDbEntity") (8 . "MASONRY") (62 . 7) (370 . 13) (100 . "AcDbLine") (10 13076.9230769231
3286.1839027149 0.0) (11 13156.1085972851 3286.1839027149 0.0))
((0 . "LINE") (100 . "AcDbEntity") (8 . "MASONRY") (62 . 7) (370 . 13) (100 . "AcDbLine") (10 13088.2352941176
1862.7453280543 0.0) (11 13095.7763122172 1862.7453280543 0.0))
((0 . "LINE") (100 . "AcDbEntity") (8 . "MASONRY") (62 . 7) (370 . 13) (100 . "AcDbLine") (10 13088.2352941176
1651.5837104072 0.0) (11 13088.2352941176 1644.0413122172 0.0))
((0 . "LINE") (100 . "AcDbEntity") (8 . "MASONRY") (62 . 7) (370 . 13) (100 . "AcDbLine") (10 13114.6309276018
1606.334841629 0.0) (11 13088.2352941176 1606.334841629 0.0))
((0 . "LINE") (100 . "AcDbEntity") (8 . "MASONRY") (62 . 7) (370 . 13) (100 . "AcDbLine") (10 13137.255361991
542.9864253394 0.0) (11 13088.2352941176 542.9864253394 0.0))
((0 . "LINE") (100 . "AcDbEntity") (8 . "MASONRY") (62 . 7) (370 . 13) (100 . "AcDbLine") (10 13103.3187104072
3531.2538687783 0.0) (11 13156.1085972851 3531.2538687783 0.0))
((0 . "LINE") (100 . "AcDbEntity") (8 . "MASONRY") (62 . 7) (370 . 13) (100 . "AcDbLine") (10 13107.0885294118
1862.7453280543 0.0) (11 13401.2061764706 1862.7453280543 0.0))
((0 . "LINE") (100 . "AcDbEntity") (8 . "MASONRY") (62 . 7) (370 . 13) (100 . "AcDbLine") (10 13124.0582352941
1185.8965158371 0.0) (11 13110.8597285068 1185.8965158371 0.0))
((0 . "LINE") (100 . "AcDbEntity") (8 . "MASONRY") (62 . 7) (370 . 13) (100 . "AcDbLine") (10 13401.2061764706
1961.4607126697 0.0) (11 13120.2870361991 1961.4607126697 0.0))
((0 . "LINE") (100 . "AcDbEntity") (8 . "MASONRY") (62 . 7) (370 . 13) (100 . "AcDbLine") (10 13120.2870361991
1961.4607126697 0.0) (11 13120.2870361991 1975.8675 0.0))
((0 . "LINE") (100 . "AcDbEntity") (8 . "MASONRY") (62 . 7) (370 . 13) (100 . "AcDbLine") (10 13114.6309276018
1104.8274660633 0.0) (11 13216.4408823529 1104.8274660633 0.0))
((0 . "LINE") (100 . "AcDbEntity") (8 . "MASONRY") (62 . 7) (370 . 13) (100 . "AcDbLine") (10 13114.6309276018
1104.8274660633 0.0) (11 13114.6309276018 1089.7426696833 0.0))
((0 . "LINE") (100 . "AcDbEntity") (8 . "MASONRY") (62 . 7) (370 . 13) (100 . "AcDbLine") (10 13124.0582352941
1185.8965158371 0.0) (11 13124.0582352941 1138.7641176471 0.0))
((0 . "LINE") (100 . "AcDbEntity") (8 . "MASONRY") (62 . 7) (370 . 13) (100 . "AcDbLine") (10 13122.1719457014
2979.0838574661 0.0) (11 13156.1085972851 2979.0838574661 0.0))
((0 . "LINE") (100 . "AcDbEntity") (8 . "MASONRY") (62 . 7) (370 . 13) (100 . "AcDbLine") (10 13124.0582352941
2941.1764705882 0.0) (11 13124.0582352941 2948.718178733 0.0))
((0 . "LINE") (100 . "AcDbEntity") (8 . "MASONRY") (62 . 7) (370 . 13) (100 . "AcDbLine") (10 13129.7143438914
2733.7860520362 0.0) (11 13129.7143438914 2711.1616176471 0.0))
((0 . "LINE") (100 . "AcDbEntity") (8 . "MASONRY") (62 . 7) (370 . 13) (100 . "AcDbLine") (10 13124.0582352941
1185.8965158371 0.0) (11 13129.7129638009 1185.8965158371 0.0))
((0 . "LINE") (100 . "AcDbEntity") (8 . "MASONRY") (62 . 7) (370 . 13) (100 . "AcDbLine") (10 13124.0582352941
1185.8965158371 0.0) (11 13124.0582352941 1255.5014479638 0.0))
((0 . "LINE") (100 . "AcDbEntity") (8 . "MASONRY") (62 . 7) (370 . 13) (100 . "AcDbLine") (10 13124.0582352941
1255.5014479638 0.0) (11 13124.0582352941 1255.6561085973 0.0))
((0 . "LINE") (100 . "AcDbEntity") (8 . "MASONRY") (62 . 7) (370 . 13) (100 . "AcDbLine") (10 13127.8280542986
3031.6742081448 0.0) (11 13127.8280542986 3076.874061086 0.0))
((0 . "LINE") (100 . "AcDbEntity") (8 . "MASONRY") (62 . 7) (370 . 13) (100 . "AcDbLine") (10 13127.8280542986
3076.874061086 0.0) (11 13156.1085972851 3076.874061086 0.0))
((0 . "LINE") (100 . "AcDbEntity") (8 . "MASONRY") (62 . 7) (370 . 13) (100 . "AcDbLine") (10 13125.9431447964
2665.9127488688 0.0) (11 13125.9431447964 2635.7466063348 0.0))
((0 . "LINE") (100 . "AcDbEntity") (8 . "MASONRY") (62 . 7) (370 . 13) (100 . "AcDbLine") (10 13125.9431447964
2635.7466063348 0.0) (11 13242.8351357466 2635.7466063348 0.0))
((0 . "LINE") (100 . "AcDbEntity") (8 . "MASONRY") (62 . 7) (370 . 13) (100 . "AcDbLine") (10 13269.2307692308
789.9509615385 0.0) (11 13125.9431447964 789.9509615385 0.0))
((0 . "LINE") (100 . "AcDbEntity") (8 . "MASONRY") (62 . 7) (370 . 13) (100 . "AcDbLine") (10 13125.9431447964
682.5028506787 0.0) (11 13133.4841628959 682.5028506787 0.0))
((0 . "LINE") (100 . "AcDbEntity") (8 . "MASONRY") (62 . 7) (370 . 13) (100 . "AcDbLine") (10 13129.7129638009
2779.0349208145 0.0) (11 13129.7129638009 2800.1859502262 0.0))
((0 . "LINE") (100 . "AcDbEntity") (8 . "MASONRY") (62 . 7) (370 . 13) (100 . "AcDbLine") (10 13159.8797963801
1753.3936651584 0.0) (11 13133.4841628959 1753.3936651584 0.0))
((0 . "LINE") (100 . "AcDbEntity") (8 . "MASONRY") (62 . 7) (370 . 13) (100 . "AcDbLine") (10 13134.0862330317
1308.4473755656 0.0) (11 13134.0862330317 1338.6114479638 0.0))
((0 . "LINE") (100 . "AcDbEntity") (8 . "MASONRY") (62 . 7) (370 . 13) (100 . "AcDbLine") (10 13134.0862330317
1338.6114479638 0.0) (11 13152.33739819 1338.6114479638 0.0))
((0 . "LINE") (100 . "AcDbEntity") (8 . "MASONRY") (62 . 7) (370 . 13) (100 . "AcDbLine") (10 13152.33739819
1338.6114479638 0.0) (11 13227.7530995475 1338.6114479638 0.0))
((0 . "LINE") (100 . "AcDbEntity") (8 . "MASONRY") (62 . 7) (370 . 13) (100 . "AcDbLine") (10 13129.7143438914
2733.7860520362 0.0) (11 13156.1085972851 2733.7860520362 0.0))
((0 . "LINE") (100 . "AcDbEntity") (8 . "MASONRY") (62 . 7) (370 . 13) (100 . "AcDbLine") (10 13137.255361991
2319.0045248869 0.0) (11 13137.255361991 2285.0678733032 0.0))
((0 . "LINE") (100 . "AcDbEntity") (8 . "MASONRY") (62 . 7) (370 . 13) (100 . "AcDbLine") (10 13137.255361991
2319.0045248869 0.0) (11 13650.0749547511 2319.0045248869 0.0))
((0 . "LINE") (100 . "AcDbEntity") (8 . "MASONRY") (62 . 7) (370 . 13) (100 . "AcDbLine") (10 13137.255361991
2156.8629751131 0.0) (11 13137.255361991 2168.1751923077 0.0))
((0 . "LINE") (100 . "AcDbEntity") (8 . "MASONRY") (62 . 7) (370 . 13) (100 . "AcDbLine") (10 13137.255361991
1602.5650226244 0.0) (11 13332.0500339367 1602.5650226244 0.0))
((0 . "LINE") (100 . "AcDbEntity") (8 . "MASONRY") (62 . 7) (370 . 13) (100 . "AcDbLine") (10 13332.0500339367
1602.5650226244 0.0) (11 13340.8752714932 1602.5650226244 0.0))
((0 . "LINE") (100 . "AcDbEntity") (8 . "MASONRY") (62 . 7) (370 . 13) (100 . "AcDbLine") (10 13124.0582352941
1255.6561085973 0.0) (11 13237.1804072398 1255.6561085973 0.0))
((0 . "LINE") (100 . "AcDbEntity") (8 . "MASONRY") (62 . 7) (370 . 13) (100 . "AcDbLine") (10 13141.0251809955
3338.9889819005 0.0) (11 13152.33739819 3338.9889819005 0.0))
((0 . "LINE") (100 . "AcDbEntity") (8 . "MASONRY") (62 . 7) (370 . 13) (100 . "AcDbLine") (10 13129.7129638009
2800.1859502262 0.0) (11 13156.1085972851 2800.1859502262 0.0))
((0 . "LINE") (100 . "AcDbEntity") (8 . "MASONRY") (62 . 7) (370 . 13) (100 . "AcDbLine") (10 13141.0251809955
2194.5701357466 0.0) (11 13159.8797963801 2194.5701357466 0.0))
((0 . "LINE") (100 . "AcDbEntity") (8 . "MASONRY") (62 . 7) (370 . 13) (100 . "AcDbLine") (10 13141.0251809955
1668.5520361991 0.0) (11 13401.2061764706 1668.5520361991 0.0))
((0 . "LINE") (100 . "AcDbEntity") (8 . "MASONRY") (62 . 7) (370 . 13) (100 . "AcDbLine") (10 13171.1920135747
629.7143438914 0.0) (11 13269.2307692308 629.7143438914 0.0))
((0 . "LINE") (100 . "AcDbEntity") (8 . "MASONRY") (62 . 7) (370 . 13) (100 . "AcDbLine") (10 13190.0452488688
2462.2928393665 0.0) (11 13178.7330316742 2462.2928393665 0.0))
((0 . "LINE") (100 . "AcDbEntity") (8 . "MASONRY") (62 . 7) (370 . 13) (100 . "AcDbLine") (10 13190.0452488688
2198.3406447964 0.0) (11 13388.0090497738 2198.3406447964 0.0))
((0 . "LINE") (100 . "AcDbEntity") (8 . "MASONRY") (62 . 7) (370 . 13) (100 . "AcDbLine") (10 13205.1286651584
1819.3820588235 0.0) (11 13193.8164479638 1819.3820588235 0.0))
((0 . "LINE") (100 . "AcDbEntity") (8 . "MASONRY") (62 . 7) (370 . 13) (100 . "AcDbLine") (10 13203.2437556561
942.6838461538 0.0) (11 13203.2437556561 837.1040723982 0.0))
((0 . "LINE") (100 . "AcDbEntity") (8 . "MASONRY") (62 . 7) (370 . 13) (100 . "AcDbLine") (10 13223.9819004525
1753.3936651584 0.0) (11 13205.1286651584 1753.3936651584 0.0))
((0 . "LINE") (100 . "AcDbEntity") (8 . "MASONRY") (62 . 7) (370 . 13) (100 . "AcDbLine") (10 13226.6028167421
530.0806674208 0.0) (11 13226.6028167421 535.4440271493 0.0))
((0 . "LINE") (100 . "AcDbEntity") (8 . "MASONRY") (62 . 7) (370 . 13) (100 . "AcDbLine") (10 13237.1804072398
1244.3438914027 0.0) (11 13237.1804072398 1255.6561085973 0.0))
((0 . "LINE") (100 . "AcDbEntity") (8 . "MASONRY") (62 . 7) (370 . 13) (100 . "AcDbLine") (10 13397.4363574661
1255.6561085973 0.0) (11 13237.1804072398 1255.6561085973 0.0))
((0 . "LINE") (100 . "AcDbEntity") (8 . "MASONRY") (62 . 7) (370 . 13) (100 . "AcDbLine") (10 13276.7717873303
1344.2689366516 0.0) (11 13246.6063348416 1344.2689366516 0.0))
((0 . "LINE") (100 . "AcDbEntity") (8 . "MASONRY") (62 . 7) (370 . 13) (100 . "AcDbLine") (10 13279.446561086
992.9681108597 0.0) (11 13246.6063348416 992.9681108597 0.0))
((0 . "LINE") (100 . "AcDbEntity") (8 . "MASONRY") (62 . 7) (370 . 13) (100 . "AcDbLine") (10 13397.4363574661
1743.9663574661 0.0) (11 13250.3775339367 1743.9663574661 0.0))
((0 . "LINE") (100 . "AcDbEntity") (8 . "MASONRY") (62 . 7) (370 . 13) (100 . "AcDbLine") (10 13273.6040384615
1380.0904977376 0.0) (11 13273.6040384615 1417.79489819 0.0))
((0 . "LINE") (100 . "AcDbEntity") (8 . "MASONRY") (62 . 7) (370 . 13) (100 . "AcDbLine") (10 13273.6040384615
1417.79489819 0.0) (11 13288.0840045249 1417.79489819 0.0))
((0 . "LINE") (100 . "AcDbEntity") (8 . "MASONRY") (62 . 7) (370 . 13) (100 . "AcDbLine") (10 13284.3128054299
2530.2434728507 0.0) (11 13284.3128054299 2586.7272285068 0.0))
((0 . "LINE") (100 . "AcDbEntity") (8 . "MASONRY") (62 . 7) (370 . 13) (100 . "AcDbLine") (10 13288.0840045249
2624.4343891403 0.0) (11 13288.0840045249 2613.1221719457 0.0))
((0 . "LINE") (100 . "AcDbEntity") (8 . "MASONRY") (62 . 7) (370 . 13) (100 . "AcDbLine") (10 13286.2764253394
1089.7426696833 0.0) (11 13286.2764253394 1101.8668438914 0.0))
((0 . "LINE") (100 . "AcDbEntity") (8 . "MASONRY") (62 . 7) (370 . 13) (100 . "AcDbLine") (10 13286.2764253394
1101.8668438914 0.0) (11 13313.3845927602 1101.8668438914 0.0))
((0 . "LINE") (100 . "AcDbEntity") (8 . "MASONRY") (62 . 7) (370 . 13) (100 . "AcDbLine") (10 13288.0840045249
2624.4343891403 0.0) (11 13288.0840045249 2658.371040724 0.0))
((0 . "LINE") (100 . "AcDbEntity") (8 . "MASONRY") (62 . 7) (370 . 13) (100 . "AcDbLine") (10 13288.0840045249
2624.4343891403 0.0) (11 13699.0950226244 2624.4343891403 0.0))
((0 . "LINE") (100 . "AcDbEntity") (8 . "MASONRY") (62 . 7) (370 . 13) (100 . "AcDbLine") (10 13284.3128054299
2530.2434728507 0.0) (11 13340.8752714932 2530.2434728507 0.0))
((0 . "LINE") (100 . "AcDbEntity") (8 . "MASONRY") (62 . 7) (370 . 13) (100 . "AcDbLine") (10 13314.4796380091
1429.1091855204 0.0) (11 13314.4796380091 1438.5364932127 0.0))
((0 . "LINE") (100 . "AcDbEntity") (8 . "MASONRY") (62 . 7) (370 . 13) (100 . "AcDbLine") (10 13310.708438914
2032.4285859729 0.0) (11 13310.708438914 2043.7470135747 0.0))
((0 . "LINE") (100 . "AcDbEntity") (8 . "MASONRY") (62 . 7) (370 . 13) (100 . "AcDbLine") (10 13310.708438914
2043.7470135747 0.0) (11 13310.708438914 2111.6141063348 0.0))
((0 . "LINE") (100 . "AcDbEntity") (8 . "MASONRY") (62 . 7) (370 . 13) (100 . "AcDbLine") (10 13397.4363574661
2111.6141063348 0.0) (11 13310.708438914 2111.6141063348 0.0))
((0 . "LINE") (100 . "AcDbEntity") (8 . "MASONRY") (62 . 7) (370 . 13) (100 . "AcDbLine") (10 13314.4796380091
1442.3076923077 0.0) (11 13314.4796380091 1474.3580542986 0.0))
((0 . "LINE") (100 . "AcDbEntity") (8 . "MASONRY") (62 . 7) (370 . 13) (100 . "AcDbLine") (10 13314.4796380091
1438.5364932127 0.0) (11 13397.4363574661 1438.5364932127 0.0))
((0 . "LINE") (100 . "AcDbEntity") (8 . "MASONRY") (62 . 7) (370 . 13) (100 . "AcDbLine") (10 13329.5630542986
1338.6114479638 0.0) (11 13397.4363574661 1338.6114479638 0.0))
((0 . "LINE") (100 . "AcDbEntity") (8 . "MASONRY") (62 . 7) (370 . 13) (100 . "AcDbLine") (10 13329.5630542986
1219.8345475113 0.0) (11 13352.1874886878 1219.8345475113 0.0))
((0 . "LINE") (100 . "AcDbEntity") (8 . "MASONRY") (62 . 7) (370 . 13) (100 . "AcDbLine") (10 13340.8752714932
1636.5016742081 0.0) (11 13340.8752714932 1602.5650226244 0.0))
((0 . "LINE") (100 . "AcDbEntity") (8 . "MASONRY") (62 . 7) (370 . 13) (100 . "AcDbLine") (10 13332.0500339367
1602.5650226244 0.0) (11 13332.0500339367 1538.465678733 0.0))
((0 . "LINE") (100 . "AcDbEntity") (8 . "MASONRY") (62 . 7) (370 . 13) (100 . "AcDbLine") (10 13332.0500339367
1538.465678733 0.0) (11 13393.665158371 1538.465678733 0.0))
((0 . "LINE") (100 . "AcDbEntity") (8 . "MASONRY") (62 . 7) (370 . 13) (100 . "AcDbLine") (10 13340.8752714932
1602.5650226244 0.0) (11 13397.4363574661 1602.5650226244 0.0))
((0 . "LINE") (100 . "AcDbEntity") (8 . "MASONRY") (62 . 7) (370 . 13) (100 . "AcDbLine") (10 13388.0090497738
2526.3949434389 0.0) (11 13363.4997058824 2526.3949434389 0.0))
((0 . "LINE") (100 . "AcDbEntity") (8 . "MASONRY") (62 . 7) (370 . 13) (100 . "AcDbLine") (10 13552.036199095
561.841040724 0.0) (11 13388.8886764706 561.841040724 0.0))
((0 . "LINE") (100 . "AcDbEntity") (8 . "MASONRY") (62 . 7) (370 . 13) (100 . "AcDbLine") (10 13470.2421832579
505.7853619909 0.0) (11 13506.7873303167 505.7853619909 0.0))
((0 . "LINE") (100 . "AcDbEntity") (8 . "MASONRY") (62 . 7) (370 . 13) (100 . "AcDbLine") (10 13388.0090497738
2526.3949434389 0.0) (11 13388.0090497738 2466.0633484163 0.0))
((0 . "LINE") (100 . "AcDbEntity") (8 . "MASONRY") (62 . 7) (370 . 13) (100 . "AcDbLine") (10 13388.0090497738
2292.609581448 0.0) (11 13388.0090497738 2198.3406447964 0.0))
((0 . "LINE") (100 . "AcDbEntity") (8 . "MASONRY") (62 . 7) (370 . 13) (100 . "AcDbLine") (10 13388.0090497738
2526.3949434389 0.0) (11 13691.5540045249 2526.3949434389 0.0))
((0 . "LINE") (100 . "AcDbEntity") (8 . "MASONRY") (62 . 7) (370 . 13) (100 . "AcDbLine") (10 13404.9773755656
2198.3406447964 0.0) (11 13388.0090497738 2198.3406447964 0.0))
((0 . "LINE") (100 . "AcDbEntity") (8 . "MASONRY") (62 . 7) (370 . 13) (100 . "AcDbLine") (10 13457.7672624434
2405.7317533937 0.0) (11 13450.2262443439 2405.7317533937 0.0))
((0 . "LINE") (100 . "AcDbEntity") (8 . "MASONRY") (62 . 7) (370 . 13) (100 . "AcDbLine") (10 13457.8487330317
1218.9466402715 0.0) (11 13457.8487330317 2314.1810859729 0.0))
((0 . "LINE") (100 . "AcDbEntity") (8 . "MASONRY") (62 . 7) (370 . 13) (100 . "AcDbLine") (10 13457.8487330317
2314.1810859729 0.0) (11 13476.6218778281 2314.1810859729 0.0))
((0 . "LINE") (100 . "AcDbEntity") (8 . "MASONRY") (62 . 7) (370 . 13) (100 . "AcDbLine") (10 13476.6218778281
2314.1810859729 0.0) (11 13569.9462895928 2314.1810859729 0.0))
((0 . "LINE") (100 . "AcDbEntity") (8 . "MASONRY") (62 . 7) (370 . 13) (100 . "AcDbLine") (10 13516.7393778281
2488.6877828054 0.0) (11 13516.7393778281 2450.9806221719 0.0))
((0 . "LINE") (100 . "AcDbEntity") (8 . "MASONRY") (62 . 7) (370 . 13) (100 . "AcDbLine") (10 13516.7393778281
2450.9806221719 0.0) (11 13516.7393778281 2413.2727714932 0.0))
((0 . "LINE") (100 . "AcDbEntity") (8 . "MASONRY") (62 . 7) (370 . 13) (100 . "AcDbLine") (10 13516.7393778281
2413.2727714932 0.0) (11 13516.7393778281 2401.9605542986 0.0))
((0 . "LINE") (100 . "AcDbEntity") (8 . "MASONRY") (62 . 7) (370 . 13) (100 . "AcDbLine") (10 13514.3283484163
2360.4828846154 0.0) (11 13521.8707466063 2360.4828846154 0.0))
((0 . "LINE") (100 . "AcDbEntity") (8 . "MASONRY") (62 . 7) (370 . 13) (100 . "AcDbLine") (10 13552.036199095
561.841040724 0.0) (11 13702.8662217195 561.841040724 0.0))
((0 . "LINE") (100 . "AcDbEntity") (8 . "MASONRY") (62 . 7) (370 . 13) (100 . "AcDbLine") (10 13719.4575678733
561.841040724 0.0) (11 14233.409479638 561.841040724 0.0))
((0 . "LINE") (100 . "AcDbEntity") (8 . "MASONRY") (62 . 7) (370 . 13) (100 . "AcDbLine") (10 14252.0224434389
563.5436764706 0.0) (11 15314.8376131222 563.5436764706 0.0))
((0 . "LINE") (100 . "AcDbEntity") (8 . "MASONRY") (62 . 7) (370 . 13) (100 . "AcDbLine") (10 15314.8376131222
563.5436764706 0.0) (11 15317.9586425339 563.5436764706 0.0))
((0 . "LINE") (100 . "AcDbEntity") (8 . "MASONRY") (62 . 7) (370 . 13) (100 . "AcDbLine") (10 15367.4785859729
565.5169570136 0.0) (11 15433.6368325792 565.5169570136 0.0))
((0 . "LINE") (100 . "AcDbEntity") (8 . "MASONRY") (62 . 7) (370 . 13) (100 . "AcDbLine") (10 13552.036199095
561.841040724 0.0) (11 13552.036199095 512.8195927602 0.0))
((0 . "LINE") (100 . "AcDbEntity") (8 . "MASONRY") (62 . 7) (370 . 13) (100 . "AcDbLine") (10 13569.9462895928
2205.8823529412 0.0) (11 13569.9462895928 2314.1810859729 0.0))
((0 . "LINE") (100 . "AcDbEntity") (8 . "MASONRY") (62 . 7) (370 . 13) (100 . "AcDbLine") (10 15659.8784162896
2205.8823529412 0.0) (11 15659.8784162896 2314.1810859729 0.0))
((0 . "LINE") (100 . "AcDbEntity") (8 . "MASONRY") (62 . 7) (370 . 13) (100 . "AcDbLine") (10 15659.8784162896
2314.1810859729 0.0) (11 15565.6108597285 2314.1810859729 0.0))
((0 . "LINE") (100 . "AcDbEntity") (8 . "MASONRY") (62 . 7) (370 . 13) (100 . "AcDbLine") (10 15565.6108597285
2314.1810859729 0.0) (11 15384.6153846154 2314.1810859729 0.0))
((0 . "LINE") (100 . "AcDbEntity") (8 . "MASONRY") (62 . 7) (370 . 13) (100 . "AcDbLine") (10 15384.6153846154
2314.1810859729 0.0) (11 15177.8309502262 2314.1810859729 0.0))
((0 . "LINE") (100 . "AcDbEntity") (8 . "MASONRY") (62 . 7) (370 . 13) (100 . "AcDbLine") (10 13996.3771945701
2314.1810859729 0.0) (11 13827.3006108597 2314.1810859729 0.0))
((0 . "LINE") (100 . "AcDbEntity") (8 . "MASONRY") (62 . 7) (370 . 13) (100 . "AcDbLine") (10 13827.3006108597
2314.1810859729 0.0) (11 13569.9462895928 2314.1810859729 0.0))
((0 . "LINE") (100 . "AcDbEntity") (8 . "MASONRY") (62 . 7) (370 . 13) (100 . "AcDbLine") (10 13706.636040724
2624.4343891403 0.0) (11 13699.0950226244 2624.4343891403 0.0))
((0 . "LINE") (100 . "AcDbEntity") (8 . "MASONRY") (62 . 7) (370 . 13) (100 . "AcDbLine") (10 13699.0950226244
2586.7272285068 0.0) (11 13699.0950226244 2624.4343891403 0.0))
((0 . "LINE") (100 . "AcDbEntity") (8 . "MASONRY") (62 . 7) (370 . 13) (100 . "AcDbLine") (10 13702.8662217195
2662.1415497738 0.0) (11 13691.5540045249 2662.1415497738 0.0))
((0 . "LINE") (100 . "AcDbEntity") (8 . "MASONRY") (62 . 7) (370 . 13) (100 . "AcDbLine") (10 13691.5540045249
2549.0193778281 0.0) (11 13691.5540045249 2526.3949434389 0.0))
((0 . "LINE") (100 . "AcDbEntity") (8 . "MASONRY") (62 . 7) (370 . 13) (100 . "AcDbLine") (10 13921.5681674208
2526.3949434389 0.0) (11 13691.5540045249 2526.3949434389 0.0))
((0 . "LINE") (100 . "AcDbEntity") (8 . "MASONRY") (62 . 7) (370 . 13) (100 . "AcDbLine") (10 13693.4389140272
2432.1266968326 0.0) (11 13693.4389140272 2473.6050565611 0.0))
((0 . "LINE") (100 . "AcDbEntity") (8 . "MASONRY") (62 . 7) (370 . 13) (100 . "AcDbLine") (10 13699.0950226244
2586.7272285068 0.0) (11 13699.0950226244 2575.4150113122 0.0))
((0 . "LINE") (100 . "AcDbEntity") (8 . "MASONRY") (62 . 7) (370 . 13) (100 . "AcDbLine") (10 13699.0950226244
2386.8778280543 0.0) (11 13815.9883936652 2386.8778280543 0.0))
((0 . "LINE") (100 . "AcDbEntity") (8 . "MASONRY") (62 . 7) (370 . 13) (100 . "AcDbLine") (10 13699.0950226244
2586.7272285068 0.0) (11 13721.7194570136 2586.7272285068 0.0))
((0 . "LINE") (100 . "AcDbEntity") (8 . "MASONRY") (62 . 7) (370 . 13) (100 . "AcDbLine") (10 13932.8803846154
2624.4343891403 0.0) (11 13914.0271493213 2624.4343891403 0.0))
((0 . "LINE") (100 . "AcDbEntity") (8 . "MASONRY") (62 . 7) (370 . 13) (100 . "AcDbLine") (10 13914.0271493213
2624.4343891403 0.0) (11 13725.4906561086 2624.4343891403 0.0))
((0 . "LINE") (100 . "AcDbEntity") (8 . "MASONRY") (62 . 7) (370 . 13) (100 . "AcDbLine") (10 13921.5681674208
2526.3949434389 0.0) (11 13921.5681674208 2571.6438122172 0.0))
((0 . "LINE") (100 . "AcDbEntity") (8 . "MASONRY") (62 . 7) (370 . 13) (100 . "AcDbLine") (10 13921.5681674208
2571.6438122172 0.0) (11 13921.5681674208 2588.0107579186 0.0))
((0 . "LINE") (100 . "AcDbEntity") (8 . "MASONRY") (62 . 7) (370 . 13) (100 . "AcDbLine") (10 13921.5681674208
2588.0107579186 0.0) (11 13744.3438914027 2588.0107579186 0.0))
((0 . "LINE") (100 . "AcDbEntity") (8 . "MASONRY") (62 . 7) (370 . 13) (100 . "AcDbLine") (10 13862.5811538462
2231.1553280543 0.0) (11 13778.0526923077 2231.1553280543 0.0))
((0 . "LINE") (100 . "AcDbEntity") (8 . "MASONRY") (62 . 7) (370 . 13) (100 . "AcDbLine") (10 13876.3192986425
514.8287782805 0.0) (11 13836.515260181 514.8287782805 0.0))
((0 . "LINE") (100 . "AcDbEntity") (8 . "MASONRY") (62 . 7) (370 . 13) (100 . "AcDbLine") (10 13842.3826470588
2269.9851470588 0.0) (11 13834.8416289593 2269.9851470588 0.0))
((0 . "LINE") (100 . "AcDbEntity") (8 . "MASONRY") (62 . 7) (370 . 13) (100 . "AcDbLine") (10 13876.3192986425
2281.2973642534 0.0) (11 13865.007081448 2281.2973642534 0.0))
((0 . "LINE") (100 . "AcDbEntity") (8 . "MASONRY") (62 . 7) (370 . 13) (100 . "AcDbLine") (10 13891.4027149321
2315.9582918552 0.0) (11 13999.7076470588 2315.9582918552 0.0))
((0 . "LINE") (100 . "AcDbEntity") (8 . "MASONRY") (62 . 7) (370 . 13) (100 . "AcDbLine") (10 15185.388438914
2310.1033371041 0.0) (11 15263.9535746606 2310.1033371041 0.0))
((0 . "LINE") (100 . "AcDbEntity") (8 . "MASONRY") (62 . 7) (370 . 13) (100 . "AcDbLine") (10 13921.5681674208
2526.3949434389 0.0) (11 13978.1292533937 2526.3949434389 0.0))
((0 . "LINE") (100 . "AcDbEntity") (8 . "MASONRY") (62 . 7) (370 . 13) (100 . "AcDbLine") (10 13978.1292533937
2526.3949434389 0.0) (11 14151.5837104072 2526.3949434389 0.0))
((0 . "LINE") (100 . "AcDbEntity") (8 . "MASONRY") (62 . 7) (370 . 13) (100 . "AcDbLine") (10 14136.5002941176
2665.9127488688 0.0) (11 13929.1105656109 2665.9127488688 0.0))
((0 . "LINE") (100 . "AcDbEntity") (8 . "MASONRY") (62 . 7) (370 . 13) (100 . "AcDbLine") (10 13937.2978393665
470.8033823529 0.0) (11 13937.2978393665 490.195158371 0.0))
((0 . "LINE") (100 . "AcDbEntity") (8 . "MASONRY") (62 . 7) (370 . 13) (100 . "AcDbLine") (10 13970.5882352941
2466.0633484163 0.0) (11 13970.5882352941 2432.1266968326 0.0))
((0 . "LINE") (100 . "AcDbEntity") (8 . "MASONRY") (62 . 7) (370 . 13) (100 . "AcDbLine") (10 13970.5882352941
2575.4150113122 0.0) (11 14095.0226244344 2575.4150113122 0.0))
((0 . "LINE") (100 . "AcDbEntity") (8 . "MASONRY") (62 . 7) (370 . 13) (100 . "AcDbLine") (10 13985.6716515837
2631.9760972851 0.0) (11 14125.1880769231 2631.9760972851 0.0))
((0 . "LINE") (100 . "AcDbEntity") (8 . "MASONRY") (62 . 7) (370 . 13) (100 . "AcDbLine") (10 14008.2960859729
516.5921719457 0.0) (11 13985.6716515837 516.5921719457 0.0))
((0 . "LINE") (100 . "AcDbEntity") (8 . "MASONRY") (62 . 7) (370 . 13) (100 . "AcDbLine") (10 14132.7304751131
2575.4150113122 0.0) (11 14151.5837104072 2575.4150113122 0.0))
((0 . "LINE") (100 . "AcDbEntity") (8 . "MASONRY") (62 . 7) (370 . 13) (100 . "AcDbLine") (10 14151.5837104072
2575.4150113122 0.0) (11 14151.5837104072 2526.3949434389 0.0))
((0 . "LINE") (100 . "AcDbEntity") (8 . "MASONRY") (62 . 7) (370 . 13) (100 . "AcDbLine") (10 14151.5837104072
2586.7265384615 0.0) (11 14151.5837104072 2575.4150113122 0.0))
((0 . "LINE") (100 . "AcDbEntity") (8 . "MASONRY") (62 . 7) (370 . 13) (100 . "AcDbLine") (10 14151.5837104072
2586.7265384615 0.0) (11 14151.5837104072 2598.0394457014 0.0))
((0 . "LINE") (100 . "AcDbEntity") (8 . "MASONRY") (62 . 7) (370 . 13) (100 . "AcDbLine") (10 14151.5837104072
2586.7265384615 0.0) (11 14174.2081447964 2586.7265384615 0.0))
((0 . "LINE") (100 . "AcDbEntity") (8 . "MASONRY") (62 . 7) (370 . 13) (100 . "AcDbLine") (10 14176.0930542986
2662.1415497738 0.0) (11 14155.3549095023 2662.1415497738 0.0))
((0 . "LINE") (100 . "AcDbEntity") (8 . "MASONRY") (62 . 7) (370 . 13) (100 . "AcDbLine") (10 14166.6671266968
2526.3949434389 0.0) (11 14151.5837104072 2526.3949434389 0.0))
((0 . "LINE") (100 . "AcDbEntity") (8 . "MASONRY") (62 . 7) (370 . 13) (100 . "AcDbLine") (10 14166.6671266968
2526.3949434389 0.0) (11 14166.6671266968 2511.3122171946 0.0))
((0 . "LINE") (100 . "AcDbEntity") (8 . "MASONRY") (62 . 7) (370 . 13) (100 . "AcDbLine") (10 14347.66260181
2526.3949434389 0.0) (11 14166.6671266968 2526.3949434389 0.0))
((0 . "LINE") (100 . "AcDbEntity") (8 . "MASONRY") (62 . 7) (370 . 13) (100 . "AcDbLine") (10 14166.6671266968
2484.9172737557 0.0) (11 14166.6671266968 2477.3755656109 0.0))
((0 . "LINE") (100 . "AcDbEntity") (8 . "MASONRY") (62 . 7) (370 . 13) (100 . "AcDbLine") (10 14176.0930542986
2662.1415497738 0.0) (11 14176.0930542986 2635.7466063348 0.0))
((0 . "LINE") (100 . "AcDbEntity") (8 . "MASONRY") (62 . 7) (370 . 13) (100 . "AcDbLine") (10 14176.0930542986
2662.1415497738 0.0) (11 14357.0885294118 2662.1415497738 0.0))
((0 . "LINE") (100 . "AcDbEntity") (8 . "MASONRY") (62 . 7) (370 . 13) (100 . "AcDbLine") (10 14351.4324208145
2582.956719457 0.0) (11 14196.8325791855 2582.956719457 0.0))
((0 . "LINE") (100 . "AcDbEntity") (8 . "MASONRY") (62 . 7) (370 . 13) (100 . "AcDbLine") (10 14309.9547511312
2631.9760972851 0.0) (11 14223.2282126697 2631.9760972851 0.0))
((0 . "LINE") (100 . "AcDbEntity") (8 . "MASONRY") (62 . 7) (370 . 13) (100 . "AcDbLine") (10 14438.1603393665
516.5907918552 0.0) (11 14371.3213235294 516.5907918552 0.0))
((0 . "LINE") (100 . "AcDbEntity") (8 . "MASONRY") (62 . 7) (370 . 13) (100 . "AcDbLine") (10 14347.66260181
2526.3949434389 0.0) (11 14347.66260181 2549.0193778281 0.0))
((0 . "LINE") (100 . "AcDbEntity") (8 . "MASONRY") (62 . 7) (370 . 13) (100 . "AcDbLine") (10 14611.6134162896
2526.3949434389 0.0) (11 14347.66260181 2526.3949434389 0.0))
((0 . "LINE") (100 . "AcDbEntity") (8 . "MASONRY") (62 . 7) (370 . 13) (100 . "AcDbLine") (10 14913.2734615385
2662.1415497738 0.0) (11 14357.0885294118 2662.1415497738 0.0))
((0 . "LINE") (100 . "AcDbEntity") (8 . "MASONRY") (62 . 7) (370 . 13) (100 . "AcDbLine") (10 14913.2734615385
2631.9760972851 0.0) (11 14357.0885294118 2631.9760972851 0.0))
((0 . "LINE") (100 . "AcDbEntity") (8 . "MASONRY") (62 . 7) (370 . 13) (100 . "AcDbLine") (10 14357.0885294118
2631.9760972851 0.0) (11 14357.0885294118 2662.1415497738 0.0))
((0 . "LINE") (100 . "AcDbEntity") (8 . "MASONRY") (62 . 7) (370 . 13) (100 . "AcDbLine") (10 14490.9502262443
476.9980316742 0.0) (11 14498.4912443439 476.9980316742 0.0))
((0 . "LINE") (100 . "AcDbEntity") (8 . "MASONRY") (62 . 7) (370 . 13) (100 . "AcDbLine") (10 14498.4912443439
501.5073755656 0.0) (11 14498.4912443439 476.9980316742 0.0))
((0 . "LINE") (100 . "AcDbEntity") (8 . "MASONRY") (62 . 7) (370 . 13) (100 . "AcDbLine") (10 14498.4912443439
465.2432352941 0.0) (11 14498.4912443439 476.9980316742 0.0))
((0 . "LINE") (100 . "AcDbEntity") (8 . "MASONRY") (62 . 7) (370 . 13) (100 . "AcDbLine") (10 14630.4680316742
501.5073755656 0.0) (11 14562.5947285068 501.5073755656 0.0))
((0 . "LINE") (100 . "AcDbEntity") (8 . "MASONRY") (62 . 7) (370 . 13) (100 . "AcDbLine") (10 14641.7802488688
2524.5093438914 0.0) (11 14868.0245927602 2524.5093438914 0.0))
((0 . "LINE") (100 . "AcDbEntity") (8 . "MASONRY") (62 . 7) (370 . 13) (100 . "AcDbLine") (10 15124.4343891403
2526.3949434389 0.0) (11 14890.6490271493 2526.3949434389 0.0))
((0 . "LINE") (100 . "AcDbEntity") (8 . "MASONRY") (62 . 7) (370 . 13) (100 . "AcDbLine") (10 15256.4084162896
2662.1415497738 0.0) (11 14913.2734615385 2662.1415497738 0.0))
((0 . "LINE") (100 . "AcDbEntity") (8 . "MASONRY") (62 . 7) (370 . 13) (100 . "AcDbLine") (10 14913.2734615385
2662.1415497738 0.0) (11 14913.2734615385 2631.9760972851 0.0))
((0 . "LINE") (100 . "AcDbEntity") (8 . "MASONRY") (62 . 7) (370 . 13) (100 . "AcDbLine") (10 15256.4084162896
2631.9760972851 0.0) (11 14913.2734615385 2631.9760972851 0.0))
((0 . "LINE") (100 . "AcDbEntity") (8 . "MASONRY") (62 . 7) (370 . 13) (100 . "AcDbLine") (10 15308.4622850679
2239.8190045249 0.0) (11 15299.3028846154 2239.8190045249 0.0))
((0 . "LINE") (100 . "AcDbEntity") (8 . "MASONRY") (62 . 7) (370 . 13) (100 . "AcDbLine") (10 15026.3956334842
516.5907918552 0.0) (11 15041.9126470588 516.5907918552 0.0))
((0 . "LINE") (100 . "AcDbEntity") (8 . "MASONRY") (62 . 7) (370 . 13) (100 . "AcDbLine") (10 15041.9126470588
516.5907918552 0.0) (11 15041.9126470588 458.5632013575 0.0))
((0 . "LINE") (100 . "AcDbEntity") (8 . "MASONRY") (62 . 7) (370 . 13) (100 . "AcDbLine") (10 15120.6631900452
2575.4150113122 0.0) (11 15128.2055882353 2575.4150113122 0.0))
((0 . "LINE") (100 . "AcDbEntity") (8 . "MASONRY") (62 . 7) (370 . 13) (100 . "AcDbLine") (10 15124.4343891403
2526.3949434389 0.0) (11 15124.4343891403 2552.7905769231 0.0))
((0 . "LINE") (100 . "AcDbEntity") (8 . "MASONRY") (62 . 7) (370 . 13) (100 . "AcDbLine") (10 15124.4343891403
2526.3949434389 0.0) (11 15331.8268778281 2526.3949434389 0.0))
((0 . "LINE") (100 . "AcDbEntity") (8 . "MASONRY") (62 . 7) (370 . 13) (100 . "AcDbLine") (10 15146.2938122172
475.3057579186 0.0) (11 15146.2938122172 520.3619909502 0.0))
((0 . "LINE") (100 . "AcDbEntity") (8 . "MASONRY") (62 . 7) (370 . 13) (100 . "AcDbLine") (10 15256.4084162896
2631.9760972851 0.0) (11 15256.4084162896 2662.1415497738 0.0))
((0 . "LINE") (100 . "AcDbEntity") (8 . "MASONRY") (62 . 7) (370 . 13) (100 . "AcDbLine") (10 15256.4084162896
2662.1415497738 0.0) (11 15541.1001357466 2662.1415497738 0.0))
((0 . "LINE") (100 . "AcDbEntity") (8 . "MASONRY") (62 . 7) (370 . 13) (100 . "AcDbLine") (10 15256.4084162896
2631.9760972851 0.0) (11 15426.0916742081 2631.9760972851 0.0))
((0 . "LINE") (100 . "AcDbEntity") (8 . "MASONRY") (62 . 7) (370 . 13) (100 . "AcDbLine") (10 15460.0283257919
2560.3315950226 0.0) (11 15429.8642533937 2560.3315950226 0.0))
((0 . "LINE") (100 . "AcDbEntity") (8 . "MASONRY") (62 . 7) (370 . 13) (100 . "AcDbLine") (10 15429.8642533937
2560.3315950226 0.0) (11 15263.9535746606 2560.3315950226 0.0))
((0 . "LINE") (100 . "AcDbEntity") (8 . "MASONRY") (62 . 7) (370 . 13) (100 . "AcDbLine") (10 15308.4622850679
2239.8190045249 0.0) (11 15308.4622850679 2233.9005316742 0.0))
((0 . "LINE") (100 . "AcDbEntity") (8 . "MASONRY") (62 . 7) (370 . 13) (100 . "AcDbLine") (10 15308.4622850679
2239.8190045249 0.0) (11 15377.0757466063 2239.8190045249 0.0))
((0 . "LINE") (100 . "AcDbEntity") (8 . "MASONRY") (62 . 7) (370 . 13) (100 . "AcDbLine") (10 15312.9695022624
2390.6490271493 0.0) (11 15426.0916742081 2390.6490271493 0.0))
((0 . "LINE") (100 . "AcDbEntity") (8 . "MASONRY") (62 . 7) (370 . 13) (100 . "AcDbLine") (10 15346.9061538462
2526.3949434389 0.0) (11 15460.0283257919 2526.3949434389 0.0))
((0 . "LINE") (100 . "AcDbEntity") (8 . "MASONRY") (62 . 7) (370 . 13) (100 . "AcDbLine") (10 15433.6368325792
565.5169570136 0.0) (11 15433.6368325792 538.3576923077 0.0))
((0 . "LINE") (100 . "AcDbEntity") (8 . "MASONRY") (62 . 7) (370 . 13) (100 . "AcDbLine") (10 15754.1556334842
565.5169570136 0.0) (11 15493.9649773756 565.5169570136 0.0))
((0 . "LINE") (100 . "AcDbEntity") (8 . "MASONRY") (62 . 7) (370 . 13) (100 . "AcDbLine") (10 15493.9649773756
565.5169570136 0.0) (11 15433.6368325792 565.5169570136 0.0))
((0 . "LINE") (100 . "AcDbEntity") (8 . "MASONRY") (62 . 7) (370 . 13) (100 . "AcDbLine") (10 15493.9649773756
2631.9760972851 0.0) (11 15437.4038914027 2631.9760972851 0.0))
((0 . "LINE") (100 . "AcDbEntity") (8 . "MASONRY") (62 . 7) (370 . 13) (100 . "AcDbLine") (10 15463.8009049774
2394.4195361991 0.0) (11 15456.2612669683 2394.4195361991 0.0))
((0 . "LINE") (100 . "AcDbEntity") (8 . "MASONRY") (62 . 7) (370 . 13) (100 . "AcDbLine") (10 15460.0283257919
2439.6684049774 0.0) (11 15460.0283257919 2526.3949434389 0.0))
((0 . "LINE") (100 . "AcDbEntity") (8 . "MASONRY") (62 . 7) (370 . 13) (100 . "AcDbLine") (10 15460.0283257919
2560.3315950226 0.0) (11 15460.0283257919 2526.3949434389 0.0))
((0 . "LINE") (100 . "AcDbEntity") (8 . "MASONRY") (62 . 7) (370 . 13) (100 . "AcDbLine") (10 15460.0283257919
2560.3315950226 0.0) (11 15799.394841629 2560.3315950226 0.0))
((0 . "LINE") (100 . "AcDbEntity") (8 . "MASONRY") (62 . 7) (370 . 13) (100 . "AcDbLine") (10 15799.394841629
2560.3315950226 0.0) (11 15810.6297285068 2560.3315950226 0.0))
((0 . "LINE") (100 . "AcDbEntity") (8 . "MASONRY") (62 . 7) (370 . 13) (100 . "AcDbLine") (10 15810.6297285068
2560.3315950226 0.0) (11 15810.6297285068 2488.6877828054 0.0))
((0 . "LINE") (100 . "AcDbEntity") (8 . "MASONRY") (62 . 7) (370 . 13) (100 . "AcDbLine") (10 15501.5101357466
2315.2340158371 0.0) (11 15720.209321267 2315.2340158371 0.0))
((0 . "LINE") (100 . "AcDbEntity") (8 . "MASONRY") (62 . 7) (370 . 13) (100 . "AcDbLine") (10 15678.7330316742
2398.1900452489 0.0) (11 15588.2352941176 2398.1900452489 0.0))
((0 . "LINE") (100 . "AcDbEntity") (8 . "MASONRY") (62 . 7) (370 . 13) (100 . "AcDbLine") (10 15588.2352941176
2398.1900452489 0.0) (11 15509.0497737557 2398.1900452489 0.0))
((0 . "LINE") (100 . "AcDbEntity") (8 . "MASONRY") (62 . 7) (370 . 13) (100 . "AcDbLine") (10 15512.8223529412
2530.1661425339 0.0) (11 15765.4581900453 2530.1661425339 0.0))
((0 . "LINE") (100 . "AcDbEntity") (8 . "MASONRY") (62 . 7) (370 . 13) (100 . "AcDbLine") (10 15529.4054072398
516.5921719457 0.0) (11 15529.4054072398 498.5653959276 0.0))
((0 . "LINE") (100 . "AcDbEntity") (8 . "MASONRY") (62 . 7) (370 . 13) (100 . "AcDbLine") (10 15541.1001357466
2662.1415497738 0.0) (11 15541.1001357466 2639.5171153846 0.0))
((0 . "LINE") (100 . "AcDbEntity") (8 . "MASONRY") (62 . 7) (370 . 13) (100 . "AcDbLine") (10 15541.1001357466
2662.1415497738 0.0) (11 15686.2726696833 2662.1415497738 0.0))
((0 . "LINE") (100 . "AcDbEntity") (8 . "MASONRY") (62 . 7) (370 . 13) (100 . "AcDbLine") (10 15591.8311199095
475.2553506787 0.0) (11 15591.8311199095 486.4253393665 0.0))
((0 . "LINE") (100 . "AcDbEntity") (8 . "MASONRY") (62 . 7) (370 . 13) (100 . "AcDbLine") (10 15599.5475113122
2633.8616968326 0.0) (11 15682.5056108597 2633.8616968326 0.0))
((0 . "LINE") (100 . "AcDbEntity") (8 . "MASONRY") (62 . 7) (370 . 13) (100 . "AcDbLine") (10 15723.9819004525
1159.2965158371 0.0) (11 15712.6696832579 1159.2965158371 0.0))
((0 . "LINE") (100 . "AcDbEntity") (8 . "MASONRY") (62 . 7) (370 . 13) (100 . "AcDbLine") (10 15760.8584615385
1121.4616176471 0.0) (11 15788.0826244344 1121.4616176471 0.0))
((0 . "LINE") (100 . "AcDbEntity") (8 . "MASONRY") (62 . 7) (370 . 13) (100 . "AcDbLine") (10 15716.4422624434
2394.4195361991 0.0) (11 15697.5848868778 2394.4195361991 0.0))
((0 . "LINE") (100 . "AcDbEntity") (8 . "MASONRY") (62 . 7) (370 . 13) (100 . "AcDbLine") (10 15696.3034276018
508.0776244344 0.0) (11 15696.3034276018 527.9043891403 0.0))
((0 . "LINE") (100 . "AcDbEntity") (8 . "MASONRY") (62 . 7) (370 . 13) (100 . "AcDbLine") (10 15716.4422624434
2349.1706674208 0.0) (11 15716.4422624434 2394.4195361991 0.0))
((0 . "LINE") (100 . "AcDbEntity") (8 . "MASONRY") (62 . 7) (370 . 13) (100 . "AcDbLine") (10 15931.3743891403
2394.4195361991 0.0) (11 15716.4422624434 2394.4195361991 0.0))
((0 . "LINE") (100 . "AcDbEntity") (8 . "MASONRY") (62 . 7) (370 . 13) (100 . "AcDbLine") (10 15731.5215384615
2266.2139479638 0.0) (11 15716.4422624434 2266.2139479638 0.0))
((0 . "LINE") (100 . "AcDbEntity") (8 . "MASONRY") (62 . 7) (370 . 13) (100 . "AcDbLine") (10 15720.209321267
2664.0271493213 0.0) (11 15731.5215384615 2664.0271493213 0.0))
((0 . "LINE") (100 . "AcDbEntity") (8 . "MASONRY") (62 . 7) (370 . 13) (100 . "AcDbLine") (10 15720.209321267
2300.1505995475 0.0) (11 15720.209321267 2315.2340158371 0.0))
((0 . "LINE") (100 . "AcDbEntity") (8 . "MASONRY") (62 . 7) (370 . 13) (100 . "AcDbLine") (10 15765.4581900453
2315.2340158371 0.0) (11 15720.209321267 2315.2340158371 0.0))
((0 . "LINE") (100 . "AcDbEntity") (8 . "MASONRY") (62 . 7) (370 . 13) (100 . "AcDbLine") (10 15801.2797511312
2115.3846153846 0.0) (11 15801.2797511312 2078.2795248869 0.0))
((0 . "LINE") (100 . "AcDbEntity") (8 . "MASONRY") (62 . 7) (370 . 13) (100 . "AcDbLine") (10 15801.2797511312
2078.2795248869 0.0) (11 15720.209321267 2078.2795248869 0.0))
((0 . "LINE") (100 . "AcDbEntity") (8 . "MASONRY") (62 . 7) (370 . 13) (100 . "AcDbLine") (10 15799.394841629
1255.6561085973 0.0) (11 15720.209321267 1255.6561085973 0.0))
((0 . "LINE") (100 . "AcDbEntity") (8 . "MASONRY") (62 . 7) (370 . 13) (100 . "AcDbLine") (10 15723.9819004525
2030.6907466063 0.0) (11 15846.53 2030.6907466063 0.0))
((0 . "LINE") (100 . "AcDbEntity") (8 . "MASONRY") (62 . 7) (370 . 13) (100 . "AcDbLine") (10 15723.9819004525
1670.4383257919 0.0) (11 15818.2522171946 1670.4383257919 0.0))
((0 . "LINE") (100 . "AcDbEntity") (8 . "MASONRY") (62 . 7) (370 . 13) (100 . "AcDbLine") (10 15791.8552036199
1285.821561086 0.0) (11 15723.9819004525 1285.821561086 0.0))
((0 . "LINE") (100 . "AcDbEntity") (8 . "MASONRY") (62 . 7) (370 . 13) (100 . "AcDbLine") (10 15846.53 1904.2229977376
0.0) (11 15727.754479638 1904.2229977376 0.0))
((0 . "LINE") (100 . "AcDbEntity") (8 . "MASONRY") (62 . 7) (370 . 13) (100 . "AcDbLine") (10 15765.4581900453
1513.9521945701 0.0) (11 15727.754479638 1513.9521945701 0.0))
((0 . "LINE") (100 . "AcDbEntity") (8 . "MASONRY") (62 . 7) (370 . 13) (100 . "AcDbLine") (10 15727.754479638
1331.0704298643 0.0) (11 15852.1888687783 1331.0704298643 0.0))
((0 . "LINE") (100 . "AcDbEntity") (8 . "MASONRY") (62 . 7) (370 . 13) (100 . "AcDbLine") (10 15731.5215384615
1459.2760180995 0.0) (11 15761.6911312217 1459.2760180995 0.0))
((0 . "LINE") (100 . "AcDbEntity") (8 . "MASONRY") (62 . 7) (370 . 13) (100 . "AcDbLine") (10 15757.9185520362
2631.9754072398 0.0) (11 15739.0666968326 2631.9754072398 0.0))
((0 . "LINE") (100 . "AcDbEntity") (8 . "MASONRY") (62 . 7) (370 . 13) (100 . "AcDbLine") (10 15754.1459728507
2263.6524095023 0.0) (11 16140.6476470588 2263.6524095023 0.0))
((0 . "LINE") (100 . "AcDbEntity") (8 . "MASONRY") (62 . 7) (370 . 13) (100 . "AcDbLine") (10 16150.0735746606
2641.4027149321 0.0) (11 16089.7454298643 2641.4027149321 0.0))
((0 . "LINE") (100 . "AcDbEntity") (8 . "MASONRY") (62 . 7) (370 . 13) (100 . "AcDbLine") (10 16089.7454298643
2641.4027149321 0.0) (11 15765.4581900453 2641.4027149321 0.0))
((0 . "LINE") (100 . "AcDbEntity") (8 . "MASONRY") (62 . 7) (370 . 13) (100 . "AcDbLine") (10 15780.5429864253
1459.2760180995 0.0) (11 15806.94 1459.2760180995 0.0))
((0 . "LINE") (100 . "AcDbEntity") (8 . "MASONRY") (62 . 7) (370 . 13) (100 . "AcDbLine") (10 15806.94 1541.0341289593
0.0) (11 15791.8552036199 1541.0341289593 0.0))
((0 . "LINE") (100 . "AcDbEntity") (8 . "MASONRY") (62 . 7) (370 . 13) (100 . "AcDbLine") (10 15804.7112556561
2239.8190045249 0.0) (11 15804.7112556561 2168.3595361991 0.0))
((0 . "LINE") (100 . "AcDbEntity") (8 . "MASONRY") (62 . 7) (370 . 13) (100 . "AcDbLine") (10 15804.7112556561
2168.3595361991 0.0) (11 15933.257918552 2168.3595361991 0.0))
((0 . "LINE") (100 . "AcDbEntity") (8 . "MASONRY") (62 . 7) (370 . 13) (100 . "AcDbLine") (10 15806.94 1421.5695475113
0.0) (11 15806.94 1459.2760180995 0.0))
((0 . "LINE") (100 . "AcDbEntity") (8 . "MASONRY") (62 . 7) (370 . 13) (100 . "AcDbLine") (10 15806.94 1476.2443438914
0.0) (11 15806.94 1459.2760180995 0.0))
((0 . "LINE") (100 . "AcDbEntity") (8 . "MASONRY") (62 . 7) (370 . 13) (100 . "AcDbLine") (10 15808.8235294118
2477.3755656109 0.0) (11 15808.8235294118 2443.4389140271 0.0))
((0 . "LINE") (100 . "AcDbEntity") (8 . "MASONRY") (62 . 7) (370 . 13) (100 . "AcDbLine") (10 15806.94 1476.2443438914
0.0) (11 15806.94 1541.0341289593 0.0))
((0 . "LINE") (100 . "AcDbEntity") (8 . "MASONRY") (62 . 7) (370 . 13) (100 . "AcDbLine") (10 16206.6374208145
1541.0341289593 0.0) (11 16059.5758371041 1541.0341289593 0.0))
((0 . "LINE") (100 . "AcDbEntity") (8 . "MASONRY") (62 . 7) (370 . 13) (100 . "AcDbLine") (10 16059.5758371041
1541.0341289593 0.0) (11 16025.6350452489 1541.0341289593 0.0))
((0 . "LINE") (100 . "AcDbEntity") (8 . "MASONRY") (62 . 7) (370 . 13) (100 . "AcDbLine") (10 16025.6350452489
1541.0341289593 0.0) (11 15806.94 1541.0341289593 0.0))
((0 . "LINE") (100 . "AcDbEntity") (8 . "MASONRY") (62 . 7) (370 . 13) (100 . "AcDbLine") (10 15814.4796380091
2590.4977375566 0.0) (11 15814.4796380091 2605.5804638009 0.0))
((0 . "LINE") (100 . "AcDbEntity") (8 . "MASONRY") (62 . 7) (370 . 13) (100 . "AcDbLine") (10 15806.94 1476.2443438914
0.0) (11 15825.7918552036 1476.2443438914 0.0))
((0 . "LINE") (100 . "AcDbEntity") (8 . "MASONRY") (62 . 7) (370 . 13) (100 . "AcDbLine") (10 15814.4796380091
1817.3417986425 0.0) (11 15829.5644343891 1817.3417986425 0.0))
((0 . "LINE") (100 . "AcDbEntity") (8 . "MASONRY") (62 . 7) (370 . 13) (100 . "AcDbLine") (10 15829.5644343891
1817.3417986425 0.0) (11 16037.5562330317 1817.3417986425 0.0))
((0 . "LINE") (100 . "AcDbEntity") (8 . "MASONRY") (62 . 7) (370 . 13) (100 . "AcDbLine") (10 16037.5562330317
1817.3417986425 0.0) (11 16037.5562330317 1866.5158371041 0.0))
((0 . "LINE") (100 . "AcDbEntity") (8 . "MASONRY") (62 . 7) (370 . 13) (100 . "AcDbLine") (10 16037.5562330317
1866.5158371041 0.0) (11 16063.3456561086 1866.5158371041 0.0))
((0 . "LINE") (100 . "AcDbEntity") (8 . "MASONRY") (62 . 7) (370 . 13) (100 . "AcDbLine") (10 15816.3659276018
1745.8512669683 0.0) (11 15816.3659276018 1768.4757013575 0.0))
((0 . "LINE") (100 . "AcDbEntity") (8 . "MASONRY") (62 . 7) (370 . 13) (100 . "AcDbLine") (10 15818.2522171946
1719.4570135747 0.0) (11 15818.2522171946 1670.4383257919 0.0))
((0 . "LINE") (100 . "AcDbEntity") (8 . "MASONRY") (62 . 7) (370 . 13) (100 . "AcDbLine") (10 16029.4117647059
1670.4383257919 0.0) (11 15818.2522171946 1670.4383257919 0.0))
((0 . "LINE") (100 . "AcDbEntity") (8 . "MASONRY") (62 . 7) (370 . 13) (100 . "AcDbLine") (10 15816.8961877828
1248.1137104072 0.0) (11 15816.8961877828 1274.5107239819 0.0))
((0 . "LINE") (100 . "AcDbEntity") (8 . "MASONRY") (62 . 7) (370 . 13) (100 . "AcDbLine") (10 15816.8961877828
1274.5107239819 0.0) (11 15829.5644343891 1274.5107239819 0.0))
((0 . "LINE") (100 . "AcDbEntity") (8 . "MASONRY") (62 . 7) (370 . 13) (100 . "AcDbLine") (10 15829.5644343891
1289.592760181 0.0) (11 15829.5644343891 1274.5107239819 0.0))
((0 . "LINE") (100 . "AcDbEntity") (8 . "MASONRY") (62 . 7) (370 . 13) (100 . "AcDbLine") (10 16508.2974660633
1274.5107239819 0.0) (11 15829.5644343891 1274.5107239819 0.0))
((0 . "LINE") (100 . "AcDbEntity") (8 . "MASONRY") (62 . 7) (370 . 13) (100 . "AcDbLine") (10 15834.8546040724
1024.5013348416 0.0) (11 15859.7285067873 1024.5013348416 0.0))
((0 . "LINE") (100 . "AcDbEntity") (8 . "MASONRY") (62 . 7) (370 . 13) (100 . "AcDbLine") (10 15833.3314932127
1084.086561086 0.0) (11 15844.6437104072 1084.086561086 0.0))
((0 . "LINE") (100 . "AcDbEntity") (8 . "MASONRY") (62 . 7) (370 . 13) (100 . "AcDbLine") (10 15963.4247511312
727.6778393665 0.0) (11 15893.665158371 727.6778393665 0.0))
((0 . "LINE") (100 . "AcDbEntity") (8 . "MASONRY") (62 . 7) (370 . 13) (100 . "AcDbLine") (10 15874.8133031674
1904.2229977376 0.0) (11 15846.53 1904.2229977376 0.0))
((0 . "LINE") (100 . "AcDbEntity") (8 . "MASONRY") (62 . 7) (370 . 13) (100 . "AcDbLine") (10 15846.53 1904.2229977376
0.0) (11 15846.53 2030.6907466063 0.0))
((0 . "LINE") (100 . "AcDbEntity") (8 . "MASONRY") (62 . 7) (370 . 13) (100 . "AcDbLine") (10 16074.6606334842
2030.6907466063 0.0) (11 15846.53 2030.6907466063 0.0))
((0 . "LINE") (100 . "AcDbEntity") (8 . "MASONRY") (62 . 7) (370 . 13) (100 . "AcDbLine") (10 16070.8880542986
1176.4705882353 0.0) (11 15848.4162895928 1176.4705882353 0.0))
((0 . "LINE") (100 . "AcDbEntity") (8 . "MASONRY") (62 . 7) (370 . 13) (100 . "AcDbLine") (10 15852.1888687783
2102.1874886878 0.0) (11 15882.3529411765 2102.1874886878 0.0))
((0 . "LINE") (100 . "AcDbEntity") (8 . "MASONRY") (62 . 7) (370 . 13) (100 . "AcDbLine") (10 15976.6232579186
957.7686425339 0.0) (11 15893.665158371 957.7686425339 0.0))
((0 . "LINE") (100 . "AcDbEntity") (8 . "MASONRY") (62 . 7) (370 . 13) (100 . "AcDbLine") (10 15863.5010859729
1093.5152488688 0.0) (11 15976.6232579186 1093.5152488688 0.0))
((0 . "LINE") (100 . "AcDbEntity") (8 . "MASONRY") (62 . 7) (370 . 13) (100 . "AcDbLine") (10 15867.2681447964
1334.8416289593 0.0) (11 15974.7369683258 1334.8416289593 0.0))
((0 . "LINE") (100 . "AcDbEntity") (8 . "MASONRY") (62 . 7) (370 . 13) (100 . "AcDbLine") (10 15893.665158371
863.4983257919 0.0) (11 15978.5067873303 863.4983257919 0.0))
((0 . "LINE") (100 . "AcDbEntity") (8 . "MASONRY") (62 . 7) (370 . 13) (100 . "AcDbLine") (10 15878.580361991
1749.6238461538 0.0) (11 15871.0407239819 1749.6238461538 0.0))
((0 . "LINE") (100 . "AcDbEntity") (8 . "MASONRY") (62 . 7) (370 . 13) (100 . "AcDbLine") (10 15871.0407239819
1380.0904977376 0.0) (11 15920.0621719457 1380.0904977376 0.0))
((0 . "LINE") (100 . "AcDbEntity") (8 . "MASONRY") (62 . 7) (370 . 13) (100 . "AcDbLine") (10 15883.3692760181
560.2143552036 0.0) (11 15883.3692760181 565.6108597285 0.0))
((0 . "LINE") (100 . "AcDbEntity") (8 . "MASONRY") (62 . 7) (370 . 13) (100 . "AcDbLine") (10 15889.8925791855
1902.33739819 0.0) (11 15923.8292307692 1902.33739819 0.0))
((0 . "LINE") (100 . "AcDbEntity") (8 . "MASONRY") (62 . 7) (370 . 13) (100 . "AcDbLine") (10 15901.2047963801
791.8552036199 0.0) (11 16327.3019909502 791.8552036199 0.0))
((0 . "LINE") (100 . "AcDbEntity") (8 . "MASONRY") (62 . 7) (370 . 13) (100 . "AcDbLine") (10 15933.257918552
2098.4162895928 0.0) (11 15920.0621719457 2098.4162895928 0.0))
((0 . "LINE") (100 . "AcDbEntity") (8 . "MASONRY") (62 . 7) (370 . 13) (100 . "AcDbLine") (10 15933.257918552
2098.4162895928 0.0) (11 16021.8721266968 2098.4162895928 0.0))
((0 . "LINE") (100 . "AcDbEntity") (8 . "MASONRY") (62 . 7) (370 . 13) (100 . "AcDbLine") (10 16021.8721266968
2098.4162895928 0.0) (11 16217.9468778281 2098.4162895928 0.0))
((0 . "LINE") (100 . "AcDbEntity") (8 . "MASONRY") (62 . 7) (370 . 13) (100 . "AcDbLine") (10 15933.257918552
2098.4162895928 0.0) (11 15933.257918552 2168.3595361991 0.0))
((0 . "LINE") (100 . "AcDbEntity") (8 . "MASONRY") (62 . 7) (370 . 13) (100 . "AcDbLine") (10 15927.6018099548
593.8914027149 0.0) (11 15952.1125339367 593.8914027149 0.0))
((0 . "LINE") (100 . "AcDbEntity") (8 . "MASONRY") (62 . 7) (370 . 13) (100 . "AcDbLine") (10 15938.9140271493
2439.6684049774 0.0) (11 15938.9140271493 2462.2928393665 0.0))
((0 . "LINE") (100 . "AcDbEntity") (8 . "MASONRY") (62 . 7) (370 . 13) (100 . "AcDbLine") (10 15931.3743891403
2394.4195361991 0.0) (11 15931.3743891403 2409.5022624434 0.0))
((0 . "LINE") (100 . "AcDbEntity") (8 . "MASONRY") (62 . 7) (370 . 13) (100 . "AcDbLine") (10 15931.3743891403
2394.4195361991 0.0) (11 16025.6391855204 2394.4195361991 0.0))
((0 . "LINE") (100 . "AcDbEntity") (8 . "MASONRY") (62 . 7) (370 . 13) (100 . "AcDbLine") (10 15965.311040724
2462.2928393665 0.0) (11 15938.9140271493 2462.2928393665 0.0))
((0 . "LINE") (100 . "AcDbEntity") (8 . "MASONRY") (62 . 7) (370 . 13) (100 . "AcDbLine") (10 16036.9514027149
2502.5663800905 0.0) (11 15938.9140271493 2502.5663800905 0.0))
((0 . "LINE") (100 . "AcDbEntity") (8 . "MASONRY") (62 . 7) (370 . 13) (100 . "AcDbLine") (10 15938.9140271493
2502.5663800905 0.0) (11 15938.9140271493 2462.2928393665 0.0))
((0 . "LINE") (100 . "AcDbEntity") (8 . "MASONRY") (62 . 7) (370 . 13) (100 . "AcDbLine") (10 15933.257918552
2168.3595361991 0.0) (11 16146.3810859729 2168.3595361991 0.0))
((0 . "LINE") (100 . "AcDbEntity") (8 . "MASONRY") (62 . 7) (370 . 13) (100 . "AcDbLine") (10 15938.9140271493
1896.5273190045 0.0) (11 15959.6521719457 1896.5273190045 0.0))
((0 . "LINE") (100 . "AcDbEntity") (8 . "MASONRY") (62 . 7) (370 . 13) (100 . "AcDbLine") (10 15974.7342081448
3240.526979638 0.0) (11 15974.7342081448 3580.3167420814 0.0))
((0 . "LINE") (100 . "AcDbEntity") (8 . "MASONRY") (62 . 7) (370 . 13) (100 . "AcDbLine") (10 15972.850678733
2760.1809954751 0.0) (11 15999.2476923077 2760.1809954751 0.0))
((0 . "LINE") (100 . "AcDbEntity") (8 . "MASONRY") (62 . 7) (370 . 13) (100 . "AcDbLine") (10 15967.1945701357
593.8914027149 0.0) (11 15952.1125339367 593.8914027149 0.0))
((0 . "LINE") (100 . "AcDbEntity") (8 . "MASONRY") (62 . 7) (370 . 13) (100 . "AcDbLine") (10 15952.1125339367
614.6295475113 0.0) (11 15952.1125339367 593.8914027149 0.0))
((0 . "LINE") (100 . "AcDbEntity") (8 . "MASONRY") (62 . 7) (370 . 13) (100 . "AcDbLine") (10 15959.6521719457
1896.5273190045 0.0) (11 15959.6521719457 1877.8280542986 0.0))
((0 . "LINE") (100 . "AcDbEntity") (8 . "MASONRY") (62 . 7) (370 . 13) (100 . "AcDbLine") (10 15959.6521719457
629.7143438914 0.0) (11 15959.6521719457 644.7963800905 0.0))
((0 . "LINE") (100 . "AcDbEntity") (8 . "MASONRY") (62 . 7) (370 . 13) (100 . "AcDbLine") (10 16063.3456561086
1866.5158371041 0.0) (11 16063.3456561086 1896.5273190045 0.0))
((0 . "LINE") (100 . "AcDbEntity") (8 . "MASONRY") (62 . 7) (370 . 13) (100 . "AcDbLine") (10 16063.3456561086
1896.5273190045 0.0) (11 15959.6521719457 1896.5273190045 0.0))
((0 . "LINE") (100 . "AcDbEntity") (8 . "MASONRY") (62 . 7) (370 . 13) (100 . "AcDbLine") (10 15963.4247511312
678.7330316742 0.0) (11 15963.4247511312 727.6778393665 0.0))
((0 . "LINE") (100 . "AcDbEntity") (8 . "MASONRY") (62 . 7) (370 . 13) (100 . "AcDbLine") (10 15963.4247511312
727.6778393665 0.0) (11 16282.0531221719 727.6778393665 0.0))
((0 . "LINE") (100 . "AcDbEntity") (8 . "MASONRY") (62 . 7) (370 . 13) (100 . "AcDbLine") (10 15967.1945701357
527.9043891403 0.0) (11 15967.1945701357 593.8914027149 0.0))
((0 . "LINE") (100 . "AcDbEntity") (8 . "MASONRY") (62 . 7) (370 . 13) (100 . "AcDbLine") (10 15967.1945701357
593.8914027149 0.0) (11 16142.5339366516 593.8914027149 0.0))
((0 . "LINE") (100 . "AcDbEntity") (8 . "MASONRY") (62 . 7) (370 . 13) (100 . "AcDbLine") (10 15974.7369683258
1470.5882352941 0.0) (11 15974.7369683258 1478.1306334842 0.0))
((0 . "LINE") (100 . "AcDbEntity") (8 . "MASONRY") (62 . 7) (370 . 13) (100 . "AcDbLine") (10 15974.7369683258
1376.320678733 0.0) (11 15974.7369683258 1334.8416289593 0.0))
((0 . "LINE") (100 . "AcDbEntity") (8 . "MASONRY") (62 . 7) (370 . 13) (100 . "AcDbLine") (10 16106.7109954751
1027.4495248869 0.0) (11 15999.2476923077 1027.4495248869 0.0))
((0 . "LINE") (100 . "AcDbEntity") (8 . "MASONRY") (62 . 7) (370 . 13) (100 . "AcDbLine") (10 15999.2476923077
1027.4495248869 0.0) (11 15971.566459276 1027.4495248869 0.0))
((0 . "LINE") (100 . "AcDbEntity") (8 . "MASONRY") (62 . 7) (370 . 13) (100 . "AcDbLine") (10 15971.566459276
1027.4495248869 0.0) (11 15971.566459276 999.2449321267 0.0))
((0 . "LINE") (100 . "AcDbEntity") (8 . "MASONRY") (62 . 7) (370 . 13) (100 . "AcDbLine") (10 15976.6232579186
1440.4214027149 0.0) (11 15976.6232579186 1414.0271493213 0.0))
((0 . "LINE") (100 . "AcDbEntity") (8 . "MASONRY") (62 . 7) (370 . 13) (100 . "AcDbLine") (10 16185.8965158371
1334.8416289593 0.0) (11 15974.7369683258 1334.8416289593 0.0))
((0 . "LINE") (100 . "AcDbEntity") (8 . "MASONRY") (62 . 7) (370 . 13) (100 . "AcDbLine") (10 15976.6232579186
1093.5152488688 0.0) (11 15976.6232579186 1067.1182352941 0.0))
((0 . "LINE") (100 . "AcDbEntity") (8 . "MASONRY") (62 . 7) (370 . 13) (100 . "AcDbLine") (10 15976.6232579186
1093.5152488688 0.0) (11 16088.5399208145 1093.5152488688 0.0))
((0 . "LINE") (100 . "AcDbEntity") (8 . "MASONRY") (62 . 7) (370 . 13) (100 . "AcDbLine") (10 16289.592760181
957.7686425339 0.0) (11 15976.6232579186 957.7686425339 0.0))
((0 . "LINE") (100 . "AcDbEntity") (8 . "MASONRY") (62 . 7) (370 . 13) (100 . "AcDbLine") (10 15976.6232579186
946.4564253394 0.0) (11 15976.6232579186 957.7686425339 0.0))
((0 . "LINE") (100 . "AcDbEntity") (8 . "MASONRY") (62 . 7) (370 . 13) (100 . "AcDbLine") (10 15978.5067873303
863.4983257919 0.0) (11 15978.5067873303 912.5197737557 0.0))
((0 . "LINE") (100 . "AcDbEntity") (8 . "MASONRY") (62 . 7) (370 . 13) (100 . "AcDbLine") (10 16070.8880542986
2850.6787330317 0.0) (11 16070.8880542986 2819.1524208145 0.0))
((0 . "LINE") (100 . "AcDbEntity") (8 . "MASONRY") (62 . 7) (370 . 13) (100 . "AcDbLine") (10 16070.8880542986
2819.1524208145 0.0) (11 15980.3903167421 2819.1524208145 0.0))
((0 . "LINE") (100 . "AcDbEntity") (8 . "MASONRY") (62 . 7) (370 . 13) (100 . "AcDbLine") (10 15980.3903167421
1749.6238461538 0.0) (11 15991.7025339367 1749.6238461538 0.0))
((0 . "LINE") (100 . "AcDbEntity") (8 . "MASONRY") (62 . 7) (370 . 13) (100 . "AcDbLine") (10 15978.5067873303
863.4983257919 0.0) (11 16010.5599095023 863.4983257919 0.0))
((0 . "LINE") (100 . "AcDbEntity") (8 . "MASONRY") (62 . 7) (370 . 13) (100 . "AcDbLine") (10 15999.2476923077
2760.1809954751 0.0) (11 15999.2476923077 2782.8054298643 0.0))
((0 . "LINE") (100 . "AcDbEntity") (8 . "MASONRY") (62 . 7) (370 . 13) (100 . "AcDbLine") (10 16067.1209954751
2760.1809954751 0.0) (11 15999.2476923077 2760.1809954751 0.0))
((0 . "LINE") (100 . "AcDbEntity") (8 . "MASONRY") (62 . 7) (370 . 13) (100 . "AcDbLine") (10 16003.0147511312
3186.2008597285 0.0) (11 16025.6391855204 3186.2008597285 0.0))
((0 . "LINE") (100 . "AcDbEntity") (8 . "MASONRY") (62 . 7) (370 . 13) (100 . "AcDbLine") (10 16025.6391855204
3186.2008597285 0.0) (11 16200.9813122172 3186.2008597285 0.0))
((0 . "LINE") (100 . "AcDbEntity") (8 . "MASONRY") (62 . 7) (370 . 13) (100 . "AcDbLine") (10 16006.7873303167
3129.7136538462 0.0) (11 16018.0995475113 3129.7136538462 0.0))
((0 . "LINE") (100 . "AcDbEntity") (8 . "MASONRY") (62 . 7) (370 . 13) (100 . "AcDbLine") (10 16018.0995475113
3129.7136538462 0.0) (11 16082.2002714932 3129.7136538462 0.0))
((0 . "LINE") (100 . "AcDbEntity") (8 . "MASONRY") (62 . 7) (370 . 13) (100 . "AcDbLine") (10 16010.5599095023
2450.9806221719 0.0) (11 16036.9514027149 2450.9806221719 0.0))
((0 . "LINE") (100 . "AcDbEntity") (8 . "MASONRY") (62 . 7) (370 . 13) (100 . "AcDbLine") (10 16014.3269683258
3042.9864253394 0.0) (11 16029.4117647059 3042.9864253394 0.0))
((0 . "LINE") (100 . "AcDbEntity") (8 . "MASONRY") (62 . 7) (370 . 13) (100 . "AcDbLine") (10 16023.7556561086
2311.4628167421 0.0) (11 16023.7556561086 2300.1505995475 0.0))
((0 . "LINE") (100 . "AcDbEntity") (8 . "MASONRY") (62 . 7) (370 . 13) (100 . "AcDbLine") (10 16172.6980090498
2971.3426131222 0.0) (11 16025.6391855204 2971.3426131222 0.0))
((0 . "LINE") (100 . "AcDbEntity") (8 . "MASONRY") (62 . 7) (370 . 13) (100 . "AcDbLine") (10 16025.6391855204
2895.92760181 0.0) (11 16085.5226809955 2895.92760181 0.0))
((0 . "LINE") (100 . "AcDbEntity") (8 . "MASONRY") (62 . 7) (370 . 13) (100 . "AcDbLine") (10 16085.5226809955
2895.92760181 0.0) (11 16342.3812669683 2895.92760181 0.0))
((0 . "LINE") (100 . "AcDbEntity") (8 . "MASONRY") (62 . 7) (370 . 13) (100 . "AcDbLine") (10 16025.6391855204
2349.1706674208 0.0) (11 16025.6391855204 2394.4195361991 0.0))
((0 . "LINE") (100 . "AcDbEntity") (8 . "MASONRY") (62 . 7) (370 . 13) (100 . "AcDbLine") (10 16138.7613574661
2394.4195361991 0.0) (11 16025.6391855204 2394.4195361991 0.0))
((0 . "LINE") (100 . "AcDbEntity") (8 . "MASONRY") (62 . 7) (370 . 13) (100 . "AcDbLine") (10 16078.4332126697
1419.6832579186 0.0) (11 16025.6391855204 1419.6832579186 0.0))
((0 . "LINE") (100 . "AcDbEntity") (8 . "MASONRY") (62 . 7) (370 . 13) (100 . "AcDbLine") (10 16029.4117647059
3470.9657692308 0.0) (11 16085.9728506787 3470.9657692308 0.0))
((0 . "LINE") (100 . "AcDbEntity") (8 . "MASONRY") (62 . 7) (370 . 13) (100 . "AcDbLine") (10 16029.4117647059
1670.4383257919 0.0) (11 16214.1798190045 1670.4383257919 0.0))
((0 . "LINE") (100 . "AcDbEntity") (8 . "MASONRY") (62 . 7) (370 . 13) (100 . "AcDbLine") (10 16029.4117647059
1670.4383257919 0.0) (11 16029.4117647059 1640.2714932127 0.0))
((0 . "LINE") (100 . "AcDbEntity") (8 . "MASONRY") (62 . 7) (370 . 13) (100 . "AcDbLine") (10 16059.5758371041
3536.9534728507 0.0) (11 16033.1843438914 3536.9534728507 0.0))
((0 . "LINE") (100 . "AcDbEntity") (8 . "MASONRY") (62 . 7) (370 . 13) (100 . "AcDbLine") (10 16127.4491402715
1606.334841629 0.0) (11 16033.1843438914 1606.334841629 0.0))
((0 . "LINE") (100 . "AcDbEntity") (8 . "MASONRY") (62 . 7) (370 . 13) (100 . "AcDbLine") (10 16059.5758371041
857.8435972851 0.0) (11 16033.1843438914 857.8435972851 0.0))
((0 . "LINE") (100 . "AcDbEntity") (8 . "MASONRY") (62 . 7) (370 . 13) (100 . "AcDbLine") (10 16036.9514027149
3337.1040723982 0.0) (11 16199.0950226244 3337.1040723982 0.0))
((0 . "LINE") (100 . "AcDbEntity") (8 . "MASONRY") (62 . 7) (370 . 13) (100 . "AcDbLine") (10 16036.9514027149
2502.5663800905 0.0) (11 16036.9514027149 2450.9806221719 0.0))
((0 . "LINE") (100 . "AcDbEntity") (8 . "MASONRY") (62 . 7) (370 . 13) (100 . "AcDbLine") (10 16089.7454298643
2502.5663800905 0.0) (11 16036.9514027149 2502.5663800905 0.0))
((0 . "LINE") (100 . "AcDbEntity") (8 . "MASONRY") (62 . 7) (370 . 13) (100 . "AcDbLine") (10 16055.8087782805
2450.9806221719 0.0) (11 16036.9514027149 2450.9806221719 0.0))
((0 . "LINE") (100 . "AcDbEntity") (8 . "MASONRY") (62 . 7) (370 . 13) (100 . "AcDbLine") (10 16153.8461538462
3267.3458597285 0.0) (11 16040.7239819005 3267.3458597285 0.0))
((0 . "LINE") (100 . "AcDbEntity") (8 . "MASONRY") (62 . 7) (370 . 13) (100 . "AcDbLine") (10 16044.493800905
1738.3116289593 0.0) (11 16044.493800905 1768.4757013575 0.0))
((0 . "LINE") (100 . "AcDbEntity") (8 . "MASONRY") (62 . 7) (370 . 13) (100 . "AcDbLine") (10 16061.4621266968
769.2307692308 0.0) (11 16061.4621266968 761.6883710407 0.0))
((0 . "LINE") (100 . "AcDbEntity") (8 . "MASONRY") (62 . 7) (370 . 13) (100 . "AcDbLine") (10 16270.7409049774
3044.8713348416 0.0) (11 16067.1209954751 3044.8713348416 0.0))
((0 . "LINE") (100 . "AcDbEntity") (8 . "MASONRY") (62 . 7) (370 . 13) (100 . "AcDbLine") (10 16067.1209954751
2760.1809954751 0.0) (11 16067.1209954751 2771.4932126697 0.0))
((0 . "LINE") (100 . "AcDbEntity") (8 . "MASONRY") (62 . 7) (370 . 13) (100 . "AcDbLine") (10 16342.3812669683
2760.1809954751 0.0) (11 16067.1209954751 2760.1809954751 0.0))
((0 . "LINE") (100 . "AcDbEntity") (8 . "MASONRY") (62 . 7) (370 . 13) (100 . "AcDbLine") (10 16184.0102262443
1866.5158371041 0.0) (11 16063.3456561086 1866.5158371041 0.0))
((0 . "LINE") (100 . "AcDbEntity") (8 . "MASONRY") (62 . 7) (370 . 13) (100 . "AcDbLine") (10 16070.8880542986
1176.4705882353 0.0) (11 16070.8880542986 1184.0129864253 0.0))
((0 . "LINE") (100 . "AcDbEntity") (8 . "MASONRY") (62 . 7) (370 . 13) (100 . "AcDbLine") (10 16070.8880542986
1176.4705882353 0.0) (11 16088.5399208145 1176.4705882353 0.0))
((0 . "LINE") (100 . "AcDbEntity") (8 . "MASONRY") (62 . 7) (370 . 13) (100 . "AcDbLine") (10 16088.5399208145
1176.4705882353 0.0) (11 16088.5399208145 1131.221719457 0.0))
((0 . "LINE") (100 . "AcDbEntity") (8 . "MASONRY") (62 . 7) (370 . 13) (100 . "AcDbLine") (10 16074.6606334842
2030.6907466063 0.0) (11 16074.6606334842 2021.1163687783 0.0))
((0 . "LINE") (100 . "AcDbEntity") (8 . "MASONRY") (62 . 7) (370 . 13) (100 . "AcDbLine") (10 16102.9411764706
2030.6907466063 0.0) (11 16074.6606334842 2030.6907466063 0.0))
((0 . "LINE") (100 . "AcDbEntity") (8 . "MASONRY") (62 . 7) (370 . 13) (100 . "AcDbLine") (10 16078.4332126697
1932.5042307692 0.0) (11 16104.8247058824 1932.5042307692 0.0))
((0 . "LINE") (100 . "AcDbEntity") (8 . "MASONRY") (62 . 7) (370 . 13) (100 . "AcDbLine") (10 16082.2002714932
3080.6935859729 0.0) (11 16082.2002714932 3088.2352941176 0.0))
((0 . "LINE") (100 . "AcDbEntity") (8 . "MASONRY") (62 . 7) (370 . 13) (100 . "AcDbLine") (10 16112.3698642534
1987.1797171946 0.0) (11 16082.2002714932 1987.1797171946 0.0))
((0 . "LINE") (100 . "AcDbEntity") (8 . "MASONRY") (62 . 7) (370 . 13) (100 . "AcDbLine") (10 16312.2171945701
1093.5152488688 0.0) (11 16115.4575226244 1093.5152488688 0.0))
((0 . "LINE") (100 . "AcDbEntity") (8 . "MASONRY") (62 . 7) (370 . 13) (100 . "AcDbLine") (10 16115.4575226244
1093.5152488688 0.0) (11 16088.5399208145 1093.5152488688 0.0))
((0 . "LINE") (100 . "AcDbEntity") (8 . "MASONRY") (62 . 7) (370 . 13) (100 . "AcDbLine") (10 16088.5399208145
1093.5152488688 0.0) (11 16088.5399208145 1131.221719457 0.0))
((0 . "LINE") (100 . "AcDbEntity") (8 . "MASONRY") (62 . 7) (370 . 13) (100 . "AcDbLine") (10 16168.9309502262
1131.221719457 0.0) (11 16088.5399208145 1131.221719457 0.0))
((0 . "LINE") (100 . "AcDbEntity") (8 . "MASONRY") (62 . 7) (370 . 13) (100 . "AcDbLine") (10 16093.5124886878
3536.9534728507 0.0) (11 16108.5972850679 3536.9534728507 0.0))
((0 . "LINE") (100 . "AcDbEntity") (8 . "MASONRY") (62 . 7) (370 . 13) (100 . "AcDbLine") (10 16191.5553846154
859.7285067873 0.0) (11 16093.5124886878 859.7285067873 0.0))
((0 . "LINE") (100 . "AcDbEntity") (8 . "MASONRY") (62 . 7) (370 . 13) (100 . "AcDbLine") (10 16691.1764705882
3469.0801696833 0.0) (11 16097.2850678733 3469.0801696833 0.0))
((0 . "LINE") (100 . "AcDbEntity") (8 . "MASONRY") (62 . 7) (370 . 13) (100 . "AcDbLine") (10 16097.2850678733
2579.1081900452 0.0) (11 16081.4463122172 2579.1081900452 0.0))
((0 . "LINE") (100 . "AcDbEntity") (8 . "MASONRY") (62 . 7) (370 . 13) (100 . "AcDbLine") (10 16081.4463122172
2579.1081900452 0.0) (11 16081.4463122172 2547.137918552 0.0))
((0 . "LINE") (100 . "AcDbEntity") (8 . "MASONRY") (62 . 7) (370 . 13) (100 . "AcDbLine") (10 16081.4463122172
2547.137918552 0.0) (11 16123.682081448 2547.137918552 0.0))
((0 . "LINE") (100 . "AcDbEntity") (8 . "MASONRY") (62 . 7) (370 . 13) (100 . "AcDbLine") (10 16208.5209502262
2030.6907466063 0.0) (11 16102.9411764706 2030.6907466063 0.0))
((0 . "LINE") (100 . "AcDbEntity") (8 . "MASONRY") (62 . 7) (370 . 13) (100 . "AcDbLine") (10 16102.9411764706
2051.281821267 0.0) (11 16102.9411764706 2030.6907466063 0.0))
((0 . "LINE") (100 . "AcDbEntity") (8 . "MASONRY") (62 . 7) (370 . 13) (100 . "AcDbLine") (10 16106.7109954751
1027.4495248869 0.0) (11 16112.3698642534 1027.4495248869 0.0))
((0 . "LINE") (100 . "AcDbEntity") (8 . "MASONRY") (62 . 7) (370 . 13) (100 . "AcDbLine") (10 16106.7109954751
1027.4495248869 0.0) (11 16106.7109954751 1040.7239819005 0.0))
((0 . "LINE") (100 . "AcDbEntity") (8 . "MASONRY") (62 . 7) (370 . 13) (100 . "AcDbLine") (10 16293.3653393665
2505.6561085973 0.0) (11 16112.3698642534 2505.6561085973 0.0))
((0 . "LINE") (100 . "AcDbEntity") (8 . "MASONRY") (62 . 7) (370 . 13) (100 . "AcDbLine") (10 16112.3698642534
1972.096300905 0.0) (11 16112.3698642534 1987.1797171946 0.0))
((0 . "LINE") (100 . "AcDbEntity") (8 . "MASONRY") (62 . 7) (370 . 13) (100 . "AcDbLine") (10 16112.3698642534
1987.1797171946 0.0) (11 16208.5209502262 1987.1797171946 0.0))
((0 . "LINE") (100 . "AcDbEntity") (8 . "MASONRY") (62 . 7) (370 . 13) (100 . "AcDbLine") (10 16112.3698642534
1180.2404072398 0.0) (11 16242.5349321267 1180.2404072398 0.0))
((0 . "LINE") (100 . "AcDbEntity") (8 . "MASONRY") (62 . 7) (370 . 13) (100 . "AcDbLine") (10 16140.6476470588
2239.8190045249 0.0) (11 16140.6476470588 2263.6524095023 0.0))
((0 . "LINE") (100 . "AcDbEntity") (8 . "MASONRY") (62 . 7) (370 . 13) (100 . "AcDbLine") (10 16140.6476470588
2263.6524095023 0.0) (11 16440.4241628959 2263.6524095023 0.0))
((0 . "LINE") (100 . "AcDbEntity") (8 . "MASONRY") (62 . 7) (370 . 13) (100 . "AcDbLine") (10 16195.3224434389
2168.3595361991 0.0) (11 16146.3810859729 2168.3595361991 0.0))
((0 . "LINE") (100 . "AcDbEntity") (8 . "MASONRY") (62 . 7) (370 . 13) (100 . "AcDbLine") (10 16217.9496380091
2190.1975565611 0.0) (11 16172.6980090498 2190.1975565611 0.0))
((0 . "LINE") (100 . "AcDbEntity") (8 . "MASONRY") (62 . 7) (370 . 13) (100 . "AcDbLine") (10 16172.6980090498
2190.1975565611 0.0) (11 16146.3810859729 2190.1975565611 0.0))
((0 . "LINE") (100 . "AcDbEntity") (8 . "MASONRY") (62 . 7) (370 . 13) (100 . "AcDbLine") (10 16146.3810859729
2190.1975565611 0.0) (11 16146.3810859729 2168.3595361991 0.0))
((0 . "LINE") (100 . "AcDbEntity") (8 . "MASONRY") (62 . 7) (370 . 13) (100 . "AcDbLine") (10 16150.0735746606
2641.4027149321 0.0) (11 16150.0735746606 2722.4738348416 0.0))
((0 . "LINE") (100 . "AcDbEntity") (8 . "MASONRY") (62 . 7) (370 . 13) (100 . "AcDbLine") (10 16150.0735746606
2641.4027149321 0.0) (11 16315.9842533937 2641.4027149321 0.0))
((0 . "LINE") (100 . "AcDbEntity") (8 . "MASONRY") (62 . 7) (370 . 13) (100 . "AcDbLine") (10 16315.9842533937
2641.4027149321 0.0) (11 16315.9842533937 2665.9127488688 0.0))
((0 . "LINE") (100 . "AcDbEntity") (8 . "MASONRY") (62 . 7) (370 . 13) (100 . "AcDbLine") (10 16150.0735746606
2599.9250452489 0.0) (11 16293.3653393665 2599.9250452489 0.0))
((0 . "LINE") (100 . "AcDbEntity") (8 . "MASONRY") (62 . 7) (370 . 13) (100 . "AcDbLine") (10 16176.4705882353
2396.3051357466 0.0) (11 16153.8461538462 2396.3051357466 0.0))
((0 . "LINE") (100 . "AcDbEntity") (8 . "MASONRY") (62 . 7) (370 . 13) (100 . "AcDbLine") (10 16185.8965158371
1334.8416289593 0.0) (11 16195.3224434389 1334.8416289593 0.0))
((0 . "LINE") (100 . "AcDbEntity") (8 . "MASONRY") (62 . 7) (370 . 13) (100 . "AcDbLine") (10 16185.8965158371
1334.8416289593 0.0) (11 16185.8965158371 1346.1538461538 0.0))
((0 . "LINE") (100 . "AcDbEntity") (8 . "MASONRY") (62 . 7) (370 . 13) (100 . "AcDbLine") (10 16187.7828054299
1421.5695475113 0.0) (11 16221.7194570136 1421.5695475113 0.0))
((0 . "LINE") (100 . "AcDbEntity") (8 . "MASONRY") (62 . 7) (370 . 13) (100 . "AcDbLine") (10 16187.7828054299
1121.7957918552 0.0) (11 16214.1798190045 1121.7957918552 0.0))
((0 . "LINE") (100 . "AcDbEntity") (8 . "MASONRY") (62 . 7) (370 . 13) (100 . "AcDbLine") (10 16199.0950226244
3267.3458597285 0.0) (11 16191.5553846154 3267.3458597285 0.0))
((0 . "LINE") (100 . "AcDbEntity") (8 . "MASONRY") (62 . 7) (370 . 13) (100 . "AcDbLine") (10 16191.5553846154
859.7285067873 0.0) (11 16304.6775565611 859.7285067873 0.0))
((0 . "LINE") (100 . "AcDbEntity") (8 . "MASONRY") (62 . 7) (370 . 13) (100 . "AcDbLine") (10 16191.5553846154
859.7285067873 0.0) (11 16191.5553846154 829.5616742081 0.0))
((0 . "LINE") (100 . "AcDbEntity") (8 . "MASONRY") (62 . 7) (370 . 13) (100 . "AcDbLine") (10 16199.0950226244
3267.3458597285 0.0) (11 16199.0950226244 3299.3969117647 0.0))
((0 . "LINE") (100 . "AcDbEntity") (8 . "MASONRY") (62 . 7) (370 . 13) (100 . "AcDbLine") (10 16199.0950226244
3267.3458597285 0.0) (11 16199.0950226244 3254.1480429864 0.0))
((0 . "LINE") (100 . "AcDbEntity") (8 . "MASONRY") (62 . 7) (370 . 13) (100 . "AcDbLine") (10 16199.0950226244
3254.1480429864 0.0) (11 16199.0950226244 3220.2113914027 0.0))
((0 . "LINE") (100 . "AcDbEntity") (8 . "MASONRY") (62 . 7) (370 . 13) (100 . "AcDbLine") (10 16200.9813122172
3205.1279751131 0.0) (11 16200.9813122172 3186.2008597285 0.0))
((0 . "LINE") (100 . "AcDbEntity") (8 . "MASONRY") (62 . 7) (370 . 13) (100 . "AcDbLine") (10 16199.0950226244
1604.4499321267 0.0) (11 16342.3812669683 1604.4499321267 0.0))
((0 . "LINE") (100 . "AcDbEntity") (8 . "MASONRY") (62 . 7) (370 . 13) (100 . "AcDbLine") (10 16210.407239819
3386.1234502262 0.0) (11 16210.407239819 3408.7478846154 0.0))
((0 . "LINE") (100 . "AcDbEntity") (8 . "MASONRY") (62 . 7) (370 . 13) (100 . "AcDbLine") (10 16210.407239819
3408.7478846154 0.0) (11 16329.185520362 3408.7478846154 0.0))
((0 . "LINE") (100 . "AcDbEntity") (8 . "MASONRY") (62 . 7) (370 . 13) (100 . "AcDbLine") (10 16327.3019909502
3186.2008597285 0.0) (11 16200.9813122172 3186.2008597285 0.0))
((0 . "LINE") (100 . "AcDbEntity") (8 . "MASONRY") (62 . 7) (370 . 13) (100 . "AcDbLine") (10 16202.86760181
1864.6309276018 0.0) (11 16233.0316742081 1864.6309276018 0.0))
((0 . "LINE") (100 . "AcDbEntity") (8 . "MASONRY") (62 . 7) (370 . 13) (100 . "AcDbLine") (10 16206.6374208145
1541.0341289593 0.0) (11 16206.6374208145 1583.7104072398 0.0))
((0 . "LINE") (100 . "AcDbEntity") (8 . "MASONRY") (62 . 7) (370 . 13) (100 . "AcDbLine") (10 16414.0271493213
3254.1480429864 0.0) (11 16199.0950226244 3254.1480429864 0.0))
((0 . "LINE") (100 . "AcDbEntity") (8 . "MASONRY") (62 . 7) (370 . 13) (100 . "AcDbLine") (10 16259.4286877828
2969.4570135747 0.0) (11 16206.6346606335 2969.4570135747 0.0))
((0 . "LINE") (100 . "AcDbEntity") (8 . "MASONRY") (62 . 7) (370 . 13) (100 . "AcDbLine") (10 16349.9264253394
1987.1797171946 0.0) (11 16208.5209502262 1987.1797171946 0.0))
((0 . "LINE") (100 . "AcDbEntity") (8 . "MASONRY") (62 . 7) (370 . 13) (100 . "AcDbLine") (10 16208.5209502262
2030.6907466063 0.0) (11 16208.5209502262 1987.1797171946 0.0))
((0 . "LINE") (100 . "AcDbEntity") (8 . "MASONRY") (62 . 7) (370 . 13) (100 . "AcDbLine") (10 16208.5209502262
2030.6907466063 0.0) (11 16432.8790045249 2030.6907466063 0.0))
((0 . "LINE") (100 . "AcDbEntity") (8 . "MASONRY") (62 . 7) (370 . 13) (100 . "AcDbLine") (10 16432.8790045249
2030.6907466063 0.0) (11 16464.9321266968 2030.6907466063 0.0))
((0 . "LINE") (100 . "AcDbEntity") (8 . "MASONRY") (62 . 7) (370 . 13) (100 . "AcDbLine") (10 16210.407239819
1734.5390497738 0.0) (11 16210.407239819 1726.9994117647 0.0))
((0 . "LINE") (100 . "AcDbEntity") (8 . "MASONRY") (62 . 7) (370 . 13) (100 . "AcDbLine") (10 16206.6374208145
1541.0341289593 0.0) (11 16515.8371040724 1541.0341289593 0.0))
((0 . "LINE") (100 . "AcDbEntity") (8 . "MASONRY") (62 . 7) (370 . 13) (100 . "AcDbLine") (10 16214.1798190045
2401.9612443439 0.0) (11 16485.6730316742 2401.9612443439 0.0))
((0 . "LINE") (100 . "AcDbEntity") (8 . "MASONRY") (62 . 7) (370 . 13) (100 . "AcDbLine") (10 16217.9496380091
2168.1751923077 0.0) (11 16217.9496380091 2190.1975565611 0.0))
((0 . "LINE") (100 . "AcDbEntity") (8 . "MASONRY") (62 . 7) (370 . 13) (100 . "AcDbLine") (10 16214.1798190045
1670.4383257919 0.0) (11 16214.1798190045 1644.0413122172 0.0))
((0 . "LINE") (100 . "AcDbEntity") (8 . "MASONRY") (62 . 7) (370 . 13) (100 . "AcDbLine") (10 16481.9004524887
1738.2342986425 0.0) (11 16338.54239819 1738.2342986425 0.0))
((0 . "LINE") (100 . "AcDbEntity") (8 . "MASONRY") (62 . 7) (370 . 13) (100 . "AcDbLine") (10 16338.54239819
1738.2342986425 0.0) (11 16338.54239819 1670.4383257919 0.0))
((0 . "LINE") (100 . "AcDbEntity") (8 . "MASONRY") (62 . 7) (370 . 13) (100 . "AcDbLine") (10 16338.54239819
1670.4383257919 0.0) (11 16214.1798190045 1670.4383257919 0.0))
((0 . "LINE") (100 . "AcDbEntity") (8 . "MASONRY") (62 . 7) (370 . 13) (100 . "AcDbLine") (10 16278.2805429864
3099.5475113122 0.0) (11 16217.9468778281 3099.5475113122 0.0))
((0 . "LINE") (100 . "AcDbEntity") (8 . "MASONRY") (62 . 7) (370 . 13) (100 . "AcDbLine") (10 16217.9468778281
2098.4162895928 0.0) (11 16217.9468778281 2070.1357466063 0.0))
((0 . "LINE") (100 . "AcDbEntity") (8 . "MASONRY") (62 . 7) (370 . 13) (100 . "AcDbLine") (10 16217.9468778281
2098.4162895928 0.0) (11 16217.9468778281 2122.9263235294 0.0))
((0 . "LINE") (100 . "AcDbEntity") (8 . "MASONRY") (62 . 7) (370 . 13) (100 . "AcDbLine") (10 16704.3722171946
2190.1975565611 0.0) (11 16217.9496380091 2190.1975565611 0.0))
((0 . "LINE") (100 . "AcDbEntity") (8 . "MASONRY") (62 . 7) (370 . 13) (100 . "AcDbLine") (10 16246.753540724
515.588959276 0.0) (11 16246.753540724 565.6108597285 0.0))
((0 . "LINE") (100 . "AcDbEntity") (8 . "MASONRY") (62 . 7) (370 . 13) (100 . "AcDbLine") (10 16339.2922285068
577.8358371041 0.0) (11 16214.8536877828 577.8358371041 0.0))
((0 . "LINE") (100 . "AcDbEntity") (8 . "MASONRY") (62 . 7) (370 . 13) (100 . "AcDbLine") (10 16214.8536877828
577.8358371041 0.0) (11 16214.8536877828 565.6108597285 0.0))
((0 . "LINE") (100 . "AcDbEntity") (8 . "MASONRY") (62 . 7) (370 . 13) (100 . "AcDbLine") (10 16214.8536877828
565.6108597285 0.0) (11 16246.753540724 565.6108597285 0.0))
((0 . "LINE") (100 . "AcDbEntity") (8 . "MASONRY") (62 . 7) (370 . 13) (100 . "AcDbLine") (10 16246.753540724
565.6108597285 0.0) (11 16304.8846945701 565.6108597285 0.0))
((0 . "LINE") (100 . "AcDbEntity") (8 . "MASONRY") (62 . 7) (370 . 13) (100 . "AcDbLine") (10 16255.6561085973
1330.469739819 0.0) (11 16238.7651131222 1330.469739819 0.0))
((0 . "LINE") (100 . "AcDbEntity") (8 . "MASONRY") (62 . 7) (370 . 13) (100 . "AcDbLine") (10 16238.7651131222
1330.469739819 0.0) (11 16238.7651131222 1312.2171945701 0.0))
((0 . "LINE") (100 . "AcDbEntity") (8 . "MASONRY") (62 . 7) (370 . 13) (100 . "AcDbLine") (10 16576.1707692308
1180.2404072398 0.0) (11 16242.5349321267 1180.2404072398 0.0))
((0 . "LINE") (100 . "AcDbEntity") (8 . "MASONRY") (62 . 7) (370 . 13) (100 . "AcDbLine") (10 16338.6114479638
1251.8862895928 0.0) (11 16338.6114479638 1231.0721945701 0.0))
((0 . "LINE") (100 . "AcDbEntity") (8 . "MASONRY") (62 . 7) (370 . 13) (100 . "AcDbLine") (10 16338.6114479638
1231.0721945701 0.0) (11 16242.5349321267 1231.0721945701 0.0))
((0 . "LINE") (100 . "AcDbEntity") (8 . "MASONRY") (62 . 7) (370 . 13) (100 . "AcDbLine") (10 16242.5349321267
1231.0721945701 0.0) (11 16242.5349321267 1180.2404072398 0.0))
((0 . "LINE") (100 . "AcDbEntity") (8 . "MASONRY") (62 . 7) (370 . 13) (100 . "AcDbLine") (10 16278.2805429864
1419.6832579186 0.0) (11 16251.8835294118 1419.6832579186 0.0))
((0 . "LINE") (100 . "AcDbEntity") (8 . "MASONRY") (62 . 7) (370 . 13) (100 . "AcDbLine") (10 16345.5517760181
1862.822658371 0.0) (11 16319.7568325792 1862.822658371 0.0))
((0 . "LINE") (100 . "AcDbEntity") (8 . "MASONRY") (62 . 7) (370 . 13) (100 . "AcDbLine") (10 16319.7568325792
1862.822658371 0.0) (11 16263.1957466063 1862.822658371 0.0))
((0 . "LINE") (100 . "AcDbEntity") (8 . "MASONRY") (62 . 7) (370 . 13) (100 . "AcDbLine") (10 16876.0190950226
1331.0718099548 0.0) (11 16278.2805429864 1331.0718099548 0.0))
((0 . "LINE") (100 . "AcDbEntity") (8 . "MASONRY") (62 . 7) (370 . 13) (100 . "AcDbLine") (10 16285.8201809955
3045.0563687783 0.0) (11 16325.2348076923 3045.0563687783 0.0))
((0 . "LINE") (100 . "AcDbEntity") (8 . "MASONRY") (62 . 7) (370 . 13) (100 . "AcDbLine") (10 16325.2348076923
3045.0563687783 0.0) (11 16325.2348076923 3099.5475113122 0.0))
((0 . "LINE") (100 . "AcDbEntity") (8 . "MASONRY") (62 . 7) (370 . 13) (100 . "AcDbLine") (10 16289.592760181
957.7686425339 0.0) (11 16289.592760181 939.0686877828 0.0))
((0 . "LINE") (100 . "AcDbEntity") (8 . "MASONRY") (62 . 7) (370 . 13) (100 . "AcDbLine") (10 16289.592760181
939.0686877828 0.0) (11 16551.6600452489 939.0686877828 0.0))
((0 . "LINE") (100 . "AcDbEntity") (8 . "MASONRY") (62 . 7) (370 . 13) (100 . "AcDbLine") (10 16289.592760181
957.7686425339 0.0) (11 16289.592760181 987.9327149321 0.0))
((0 . "LINE") (100 . "AcDbEntity") (8 . "MASONRY") (62 . 7) (370 . 13) (100 . "AcDbLine") (10 16293.3653393665
886.1241402715 0.0) (11 16414.0271493213 886.1241402715 0.0))
((0 . "LINE") (100 . "AcDbEntity") (8 . "MASONRY") (62 . 7) (370 . 13) (100 . "AcDbLine") (10 16387.6301357466
1421.5695475113 0.0) (11 16297.13239819 1421.5695475113 0.0))
((0 . "LINE") (100 . "AcDbEntity") (8 . "MASONRY") (62 . 7) (370 . 13) (100 . "AcDbLine") (10 16304.6775565611
3099.5475113122 0.0) (11 16325.2348076923 3099.5475113122 0.0))
((0 . "LINE") (100 . "AcDbEntity") (8 . "MASONRY") (62 . 7) (370 . 13) (100 . "AcDbLine") (10 16312.2171945701
2507.5417081448 0.0) (11 16327.3019909502 2507.5417081448 0.0))
((0 . "LINE") (100 . "AcDbEntity") (8 . "MASONRY") (62 . 7) (370 . 13) (100 . "AcDbLine") (10 16329.185520362
3374.8112330317 0.0) (11 16329.185520362 3408.7478846154 0.0))
((0 . "LINE") (100 . "AcDbEntity") (8 . "MASONRY") (62 . 7) (370 . 13) (100 . "AcDbLine") (10 16329.185520362
3408.7478846154 0.0) (11 16417.7997285068 3408.7478846154 0.0))
((0 . "LINE") (100 . "AcDbEntity") (8 . "MASONRY") (62 . 7) (370 . 13) (100 . "AcDbLine") (10 16327.3019909502
3186.2008597285 0.0) (11 16327.3019909502 3212.6696832579 0.0))
((0 . "LINE") (100 . "AcDbEntity") (8 . "MASONRY") (62 . 7) (370 . 13) (100 . "AcDbLine") (10 16327.3019909502
3186.2008597285 0.0) (11 16349.9264253394 3186.2008597285 0.0))
((0 . "LINE") (100 . "AcDbEntity") (8 . "MASONRY") (62 . 7) (370 . 13) (100 . "AcDbLine") (10 16349.9264253394
3186.2008597285 0.0) (11 16395.1752941176 3186.2008597285 0.0))
((0 . "LINE") (100 . "AcDbEntity") (8 . "MASONRY") (62 . 7) (370 . 13) (100 . "AcDbLine") (10 16417.7997285068
3099.5475113122 0.0) (11 16325.2348076923 3099.5475113122 0.0))
((0 . "LINE") (100 . "AcDbEntity") (8 . "MASONRY") (62 . 7) (370 . 13) (100 . "AcDbLine") (10 16327.3019909502
2714.9321266968 0.0) (11 16327.3019909502 2722.4738348416 0.0))
((0 . "LINE") (100 . "AcDbEntity") (8 . "MASONRY") (62 . 7) (370 . 13) (100 . "AcDbLine") (10 16327.3019909502
2507.5417081448 0.0) (11 16421.5667873303 2507.5417081448 0.0))
((0 . "LINE") (100 . "AcDbEntity") (8 . "MASONRY") (62 . 7) (370 . 13) (100 . "AcDbLine") (10 16327.3019909502
2507.5417081448 0.0) (11 16327.3019909502 2590.4977375566 0.0))
((0 . "LINE") (100 . "AcDbEntity") (8 . "MASONRY") (62 . 7) (370 . 13) (100 . "AcDbLine") (10 16327.3019909502
2590.4977375566 0.0) (11 16327.3019909502 2622.471459276 0.0))
((0 . "LINE") (100 . "AcDbEntity") (8 . "MASONRY") (62 . 7) (370 . 13) (100 . "AcDbLine") (10 16327.3019909502
2622.471459276 0.0) (11 16410.2545701357 2622.471459276 0.0))
((0 . "LINE") (100 . "AcDbEntity") (8 . "MASONRY") (62 . 7) (370 . 13) (100 . "AcDbLine") (10 16345.5517760181
1862.822658371 0.0) (11 16345.5517760181 1894.7190497738 0.0))
((0 . "LINE") (100 . "AcDbEntity") (8 . "MASONRY") (62 . 7) (370 . 13) (100 . "AcDbLine") (10 16345.5517760181
1894.7190497738 0.0) (11 16327.3019909502 1894.7190497738 0.0))
((0 . "LINE") (100 . "AcDbEntity") (8 . "MASONRY") (62 . 7) (370 . 13) (100 . "AcDbLine") (10 16327.3019909502
1817.4971493213 0.0) (11 16338.6142081448 1817.4971493213 0.0))
((0 . "LINE") (100 . "AcDbEntity") (8 . "MASONRY") (62 . 7) (370 . 13) (100 . "AcDbLine") (10 16327.3019909502
723.9819004525 0.0) (11 16346.1538461538 723.9819004525 0.0))
((0 . "LINE") (100 . "AcDbEntity") (8 . "MASONRY") (62 . 7) (370 . 13) (100 . "AcDbLine") (10 16338.6142081448
3337.1040723982 0.0) (11 16349.9264253394 3337.1040723982 0.0))
((0 . "LINE") (100 . "AcDbEntity") (8 . "MASONRY") (62 . 7) (370 . 13) (100 . "AcDbLine") (10 16349.9264253394
3337.1040723982 0.0) (11 16417.7997285068 3337.1040723982 0.0))
((0 . "LINE") (100 . "AcDbEntity") (8 . "MASONRY") (62 . 7) (370 . 13) (100 . "AcDbLine") (10 16414.0271493213
2828.0542986425 0.0) (11 16342.3812669683 2828.0542986425 0.0))
((0 . "LINE") (100 . "AcDbEntity") (8 . "MASONRY") (62 . 7) (370 . 13) (100 . "AcDbLine") (10 16342.3812669683
2760.1809954751 0.0) (11 16342.3812669683 2828.0542986425 0.0))
((0 . "LINE") (100 . "AcDbEntity") (8 . "MASONRY") (62 . 7) (370 . 13) (100 . "AcDbLine") (10 16342.3812669683
2828.0542986425 0.0) (11 16342.3812669683 2895.92760181 0.0))
((0 . "LINE") (100 . "AcDbEntity") (8 . "MASONRY") (62 . 7) (370 . 13) (100 . "AcDbLine") (10 16342.3812669683
2760.1809954751 0.0) (11 16417.7997285068 2760.1809954751 0.0))
((0 . "LINE") (100 . "AcDbEntity") (8 . "MASONRY") (62 . 7) (370 . 13) (100 . "AcDbLine") (10 16361.2386425339
3142.910780543 0.0) (11 16346.1538461538 3142.910780543 0.0))
((0 . "LINE") (100 . "AcDbEntity") (8 . "MASONRY") (62 . 7) (370 . 13) (100 . "AcDbLine") (10 16414.0271493213
2895.92760181 0.0) (11 16342.3812669683 2895.92760181 0.0))
((0 . "LINE") (100 . "AcDbEntity") (8 . "MASONRY") (62 . 7) (370 . 13) (100 . "AcDbLine") (10 16345.5517760181
1862.822658371 0.0) (11 16376.317918552 1862.822658371 0.0))
((0 . "LINE") (100 . "AcDbEntity") (8 . "MASONRY") (62 . 7) (370 . 13) (100 . "AcDbLine") (10 16376.317918552
1862.822658371 0.0) (11 16538.4615384615 1862.822658371 0.0))
((0 . "LINE") (100 . "AcDbEntity") (8 . "MASONRY") (62 . 7) (370 . 13) (100 . "AcDbLine") (10 16349.9264253394
1078.4318325792 0.0) (11 16581.8241176471 1078.4318325792 0.0))
((0 . "LINE") (100 . "AcDbEntity") (8 . "MASONRY") (62 . 7) (370 . 13) (100 . "AcDbLine") (10 16349.9264253394
617.9547171946 0.0) (11 16357.9687104072 617.9547171946 0.0))
((0 . "LINE") (100 . "AcDbEntity") (8 . "MASONRY") (62 . 7) (370 . 13) (100 . "AcDbLine") (10 16595.0226244344
1953.2423755656 0.0) (11 16357.4660633484 1953.2423755656 0.0))
((0 . "LINE") (100 . "AcDbEntity") (8 . "MASONRY") (62 . 7) (370 . 13) (100 . "AcDbLine") (10 16365.0057013575
2598.0394457014 0.0) (11 16417.7997285068 2598.0394457014 0.0))
((0 . "LINE") (100 . "AcDbEntity") (8 . "MASONRY") (62 . 7) (370 . 13) (100 . "AcDbLine") (10 16417.7997285068
3029.7892986425 0.0) (11 16368.778280543 3029.7892986425 0.0))
((0 . "LINE") (100 . "AcDbEntity") (8 . "MASONRY") (62 . 7) (370 . 13) (100 . "AcDbLine") (10 16383.8630769231
1685.520361991 0.0) (11 16653.47 1685.520361991 0.0))
((0 . "LINE") (100 . "AcDbEntity") (8 . "MASONRY") (62 . 7) (370 . 13) (100 . "AcDbLine") (10 16387.6301357466
812.7452488688 0.0) (11 16387.6301357466 825.7918552036 0.0))
((0 . "LINE") (100 . "AcDbEntity") (8 . "MASONRY") (62 . 7) (370 . 13) (100 . "AcDbLine") (10 16387.6301357466
1421.5695475113 0.0) (11 16387.6301357466 1455.506199095 0.0))
((0 . "LINE") (100 . "AcDbEntity") (8 . "MASONRY") (62 . 7) (370 . 13) (100 . "AcDbLine") (10 16387.6301357466
1421.5695475113 0.0) (11 16387.6301357466 1402.7922624434 0.0))
((0 . "LINE") (100 . "AcDbEntity") (8 . "MASONRY") (62 . 7) (370 . 13) (100 . "AcDbLine") (10 16387.6301357466
1365.0084615385 0.0) (11 16387.6301357466 1402.7922624434 0.0))
((0 . "LINE") (100 . "AcDbEntity") (8 . "MASONRY") (62 . 7) (370 . 13) (100 . "AcDbLine") (10 16416.8510633484
812.7452488688 0.0) (11 16387.6301357466 812.7452488688 0.0))
((0 . "LINE") (100 . "AcDbEntity") (8 . "MASONRY") (62 . 7) (370 . 13) (100 . "AcDbLine") (10 16387.6301357466
812.7452488688 0.0) (11 16387.6301357466 755.6545927602 0.0))
((0 . "LINE") (100 . "AcDbEntity") (8 . "MASONRY") (62 . 7) (370 . 13) (100 . "AcDbLine") (10 16417.7997285068
2554.6761764706 0.0) (11 16391.4027149321 2554.6761764706 0.0))
((0 . "LINE") (100 . "AcDbEntity") (8 . "MASONRY") (62 . 7) (370 . 13) (100 . "AcDbLine") (10 16387.6301357466
1402.7922624434 0.0) (11 16593.1363348416 1402.7922624434 0.0))
((0 . "LINE") (100 . "AcDbEntity") (8 . "MASONRY") (62 . 7) (370 . 13) (100 . "AcDbLine") (10 16593.1363348416
1402.7922624434 0.0) (11 16593.1363348416 1425.3393665158 0.0))
((0 . "LINE") (100 . "AcDbEntity") (8 . "MASONRY") (62 . 7) (370 . 13) (100 . "AcDbLine") (10 16415.913438914
3148.5668891403 0.0) (11 16415.913438914 3137.2546719457 0.0))
((0 . "LINE") (100 . "AcDbEntity") (8 . "MASONRY") (62 . 7) (370 . 13) (100 . "AcDbLine") (10 16521.4932126697
2263.6524095023 0.0) (11 16508.2974660633 2263.6524095023 0.0))
((0 . "LINE") (100 . "AcDbEntity") (8 . "MASONRY") (62 . 7) (370 . 13) (100 . "AcDbLine") (10 16508.2974660633
2263.6524095023 0.0) (11 16474.3608144796 2263.6524095023 0.0))
((0 . "LINE") (100 . "AcDbEntity") (8 . "MASONRY") (62 . 7) (370 . 13) (100 . "AcDbLine") (10 16474.3608144796
2263.6524095023 0.0) (11 16451.740520362 2263.6524095023 0.0))
((0 . "LINE") (100 . "AcDbEntity") (8 . "MASONRY") (62 . 7) (370 . 13) (100 . "AcDbLine") (10 16451.740520362
2263.6524095023 0.0) (11 16440.4241628959 2263.6524095023 0.0))
((0 . "LINE") (100 . "AcDbEntity") (8 . "MASONRY") (62 . 7) (370 . 13) (100 . "AcDbLine") (10 16444.1912217195
2100.3018891403 0.0) (11 16464.9321266968 2100.3018891403 0.0))
((0 . "LINE") (100 . "AcDbEntity") (8 . "MASONRY") (62 . 7) (370 . 13) (100 . "AcDbLine") (10 16450.4521606335
995.4751131222 0.0) (11 16444.1912217195 995.4751131222 0.0))
((0 . "LINE") (100 . "AcDbEntity") (8 . "MASONRY") (62 . 7) (370 . 13) (100 . "AcDbLine") (10 16450.4521606335
995.4751131222 0.0) (11 16450.4521606335 1027.5234049774 0.0))
((0 . "LINE") (100 . "AcDbEntity") (8 . "MASONRY") (62 . 7) (370 . 13) (100 . "AcDbLine") (10 16450.4521606335
1027.5234049774 0.0) (11 16470.5882352941 1027.5234049774 0.0))
((0 . "LINE") (100 . "AcDbEntity") (8 . "MASONRY") (62 . 7) (370 . 13) (100 . "AcDbLine") (10 16450.4521606335
995.4751131222 0.0) (11 16745.8540271493 995.4751131222 0.0))
((0 . "LINE") (100 . "AcDbEntity") (8 . "MASONRY") (62 . 7) (370 . 13) (100 . "AcDbLine") (10 16542.2341176471
888.0090497738 0.0) (11 16451.7363800905 888.0090497738 0.0))
((0 . "LINE") (100 . "AcDbEntity") (8 . "MASONRY") (62 . 7) (370 . 13) (100 . "AcDbLine") (10 16666.6685067873
2317.1196153846 0.0) (11 16459.2760180996 2317.1196153846 0.0))
((0 . "LINE") (100 . "AcDbEntity") (8 . "MASONRY") (62 . 7) (370 . 13) (100 . "AcDbLine") (10 16464.9321266968
2100.3018891403 0.0) (11 16464.9321266968 2030.6907466063 0.0))
((0 . "LINE") (100 . "AcDbEntity") (8 . "MASONRY") (62 . 7) (370 . 13) (100 . "AcDbLine") (10 16523.3767420815
2100.3018891403 0.0) (11 16464.9321266968 2100.3018891403 0.0))
((0 . "LINE") (100 . "AcDbEntity") (8 . "MASONRY") (62 . 7) (370 . 13) (100 . "AcDbLine") (10 16478.1278733032
2030.6907466063 0.0) (11 16464.9321266968 2030.6907466063 0.0))
((0 . "LINE") (100 . "AcDbEntity") (8 . "MASONRY") (62 . 7) (370 . 13) (100 . "AcDbLine") (10 16481.9004524887
825.7918552036 0.0) (11 16606.334841629 825.7918552036 0.0))
((0 . "LINE") (100 . "AcDbEntity") (8 . "MASONRY") (62 . 7) (370 . 13) (100 . "AcDbLine") (10 16500.7523076923
1598.7924434389 0.0) (11 16515.8371040724 1598.7924434389 0.0))
((0 . "LINE") (100 . "AcDbEntity") (8 . "MASONRY") (62 . 7) (370 . 13) (100 . "AcDbLine") (10 16504.5248868778
3535.0678733032 0.0) (11 16512.0645248869 3535.0678733032 0.0))
((0 . "LINE") (100 . "AcDbEntity") (8 . "MASONRY") (62 . 7) (370 . 13) (100 . "AcDbLine") (10 16517.7233936652
1463.0458371041 0.0) (11 16508.2974660633 1463.0458371041 0.0))
((0 . "LINE") (100 . "AcDbEntity") (8 . "MASONRY") (62 . 7) (370 . 13) (100 . "AcDbLine") (10 16508.2974660633
1274.5107239819 0.0) (11 16508.2974660633 1255.6561085973 0.0))
((0 . "LINE") (100 . "AcDbEntity") (8 . "MASONRY") (62 . 7) (370 . 13) (100 . "AcDbLine") (10 16508.2974660633
1285.8229411765 0.0) (11 16508.2974660633 1274.5107239819 0.0))
((0 . "LINE") (100 . "AcDbEntity") (8 . "MASONRY") (62 . 7) (370 . 13) (100 . "AcDbLine") (10 16512.0645248869
2409.5768325792 0.0) (11 16542.2341176471 2409.5768325792 0.0))
((0 . "LINE") (100 . "AcDbEntity") (8 . "MASONRY") (62 . 7) (370 . 13) (100 . "AcDbLine") (10 16542.2341176471
2409.5768325792 0.0) (11 16542.2341176471 2424.5849886878 0.0))
((0 . "LINE") (100 . "AcDbEntity") (8 . "MASONRY") (62 . 7) (370 . 13) (100 . "AcDbLine") (10 16583.7104072398
2036.1990950226 0.0) (11 16512.0645248869 2036.1990950226 0.0))
((0 . "LINE") (100 . "AcDbEntity") (8 . "MASONRY") (62 . 7) (370 . 13) (100 . "AcDbLine") (10 16519.6096832579
1233.0316742081 0.0) (11 16512.0645248869 1233.0316742081 0.0))
((0 . "LINE") (100 . "AcDbEntity") (8 . "MASONRY") (62 . 7) (370 . 13) (100 . "AcDbLine") (10 16538.4615384615
1598.7924434389 0.0) (11 16515.8371040724 1598.7924434389 0.0))
((0 . "LINE") (100 . "AcDbEntity") (8 . "MASONRY") (62 . 7) (370 . 13) (100 . "AcDbLine") (10 16515.8371040724
1598.7924434389 0.0) (11 16515.8371040724 1541.0341289593 0.0))
((0 . "LINE") (100 . "AcDbEntity") (8 . "MASONRY") (62 . 7) (370 . 13) (100 . "AcDbLine") (10 16866.5158371041
1541.0341289593 0.0) (11 16515.8371040724 1541.0341289593 0.0))
((0 . "LINE") (100 . "AcDbEntity") (8 . "MASONRY") (62 . 7) (370 . 13) (100 . "AcDbLine") (10 16681.7477828054
1463.0458371041 0.0) (11 16517.7233936652 1463.0458371041 0.0))
((0 . "LINE") (100 . "AcDbEntity") (8 . "MASONRY") (62 . 7) (370 . 13) (100 . "AcDbLine") (10 16517.7233936652
1463.0458371041 0.0) (11 16517.7233936652 1500.7550678733 0.0))
((0 . "LINE") (100 . "AcDbEntity") (8 . "MASONRY") (62 . 7) (370 . 13) (100 . "AcDbLine") (10 16521.4932126697
2263.6524095023 0.0) (11 16521.4932126697 2232.2772963801 0.0))
((0 . "LINE") (100 . "AcDbEntity") (8 . "MASONRY") (62 . 7) (370 . 13) (100 . "AcDbLine") (10 16521.4932126697
2263.6524095023 0.0) (11 16704.3722171946 2263.6524095023 0.0))
((0 . "LINE") (100 . "AcDbEntity") (8 . "MASONRY") (62 . 7) (370 . 13) (100 . "AcDbLine") (10 16523.3767420815
1742.0814479638 0.0) (11 16549.7737556561 1742.0814479638 0.0))
((0 . "LINE") (100 . "AcDbEntity") (8 . "MASONRY") (62 . 7) (370 . 13) (100 . "AcDbLine") (10 16538.4615384615
1862.822658371 0.0) (11 16538.4615384615 1810.556821267 0.0))
((0 . "LINE") (100 . "AcDbEntity") (8 . "MASONRY") (62 . 7) (370 . 13) (100 . "AcDbLine") (10 16538.4615384615
1862.822658371 0.0) (11 16634.6153846154 1862.822658371 0.0))
((0 . "LINE") (100 . "AcDbEntity") (8 . "MASONRY") (62 . 7) (370 . 13) (100 . "AcDbLine") (10 16538.4615384615
1779.787918552 0.0) (11 16538.4615384615 1810.556821267 0.0))
((0 . "LINE") (100 . "AcDbEntity") (8 . "MASONRY") (62 . 7) (370 . 13) (100 . "AcDbLine") (10 16542.2341176471
2458.5216402715 0.0) (11 16542.2341176471 2424.5849886878 0.0))
((0 . "LINE") (100 . "AcDbEntity") (8 . "MASONRY") (62 . 7) (370 . 13) (100 . "AcDbLine") (10 16713.8009049774
1862.822658371 0.0) (11 16713.8009049774 1810.556821267 0.0))
((0 . "LINE") (100 . "AcDbEntity") (8 . "MASONRY") (62 . 7) (370 . 13) (100 . "AcDbLine") (10 16713.8009049774
1810.556821267 0.0) (11 16538.4615384615 1810.556821267 0.0))
((0 . "LINE") (100 . "AcDbEntity") (8 . "MASONRY") (62 . 7) (370 . 13) (100 . "AcDbLine") (10 16542.2341176471
2424.5849886878 0.0) (11 16674.2081447964 2424.5849886878 0.0))
((0 . "LINE") (100 . "AcDbEntity") (8 . "MASONRY") (62 . 7) (370 . 13) (100 . "AcDbLine") (10 16551.6600452489
939.0686877828 0.0) (11 16551.6600452489 920.0594117647 0.0))
((0 . "LINE") (100 . "AcDbEntity") (8 . "MASONRY") (62 . 7) (370 . 13) (100 . "AcDbLine") (10 16551.6600452489
939.0686877828 0.0) (11 16602.5622624434 939.0686877828 0.0))
((0 . "LINE") (100 . "AcDbEntity") (8 . "MASONRY") (62 . 7) (370 . 13) (100 . "AcDbLine") (10 16653.47 1600.6787330317
0.0) (11 16557.3133936652 1600.6787330317 0.0))
((0 . "LINE") (100 . "AcDbEntity") (8 . "MASONRY") (62 . 7) (370 . 13) (100 . "AcDbLine") (10 16568.6256108597
1285.8229411765 0.0) (11 16561.0859728507 1285.8229411765 0.0))
((0 . "LINE") (100 . "AcDbEntity") (8 . "MASONRY") (62 . 7) (370 . 13) (100 . "AcDbLine") (10 16595.0226244344
2107.8429072398 0.0) (11 16564.8585520362 2107.8429072398 0.0))
((0 . "LINE") (100 . "AcDbEntity") (8 . "MASONRY") (62 . 7) (370 . 13) (100 . "AcDbLine") (10 16633.074321267
686.9817533937 0.0) (11 16633.074321267 806.6907466063 0.0))
((0 . "LINE") (100 . "AcDbEntity") (8 . "MASONRY") (62 . 7) (370 . 13) (100 . "AcDbLine") (10 16705.0460859729
851.7663235294 0.0) (11 16724.3315384615 851.7663235294 0.0))
((0 . "LINE") (100 . "AcDbEntity") (8 . "MASONRY") (62 . 7) (370 . 13) (100 . "AcDbLine") (10 16724.3315384615
851.7663235294 0.0) (11 16724.3315384615 815.012658371 0.0))
((0 . "LINE") (100 . "AcDbEntity") (8 . "MASONRY") (62 . 7) (370 . 13) (100 . "AcDbLine") (10 16576.1707692308
1180.2404072398 0.0) (11 16576.1707692308 1168.9281900452 0.0))
((0 . "LINE") (100 . "AcDbEntity") (8 . "MASONRY") (62 . 7) (370 . 13) (100 . "AcDbLine") (10 16576.1707692308
1180.2404072398 0.0) (11 16693.06 1180.2404072398 0.0))
((0 . "LINE") (100 . "AcDbEntity") (8 . "MASONRY") (62 . 7) (370 . 13) (100 . "AcDbLine") (10 16636.4989140272
3508.6729298643 0.0) (11 16579.9378280543 3508.6729298643 0.0))
((0 . "LINE") (100 . "AcDbEntity") (8 . "MASONRY") (62 . 7) (370 . 13) (100 . "AcDbLine") (10 17179.4853393665
1743.9663574661 0.0) (11 16579.9378280543 1743.9663574661 0.0))
((0 . "LINE") (100 . "AcDbEntity") (8 . "MASONRY") (62 . 7) (370 . 13) (100 . "AcDbLine") (10 16579.9378280543
1121.7944117647 0.0) (11 16659.1233484163 1121.7944117647 0.0))
((0 . "LINE") (100 . "AcDbEntity") (8 . "MASONRY") (62 . 7) (370 . 13) (100 . "AcDbLine") (10 16581.8241176471
1078.4318325792 0.0) (11 16581.8241176471 1093.5152488688 0.0))
((0 . "LINE") (100 . "AcDbEntity") (8 . "MASONRY") (62 . 7) (370 . 13) (100 . "AcDbLine") (10 16581.8241176471
1078.4318325792 0.0) (11 17075.7918552036 1078.4318325792 0.0))
((0 . "LINE") (100 . "AcDbEntity") (8 . "MASONRY") (62 . 7) (370 . 13) (100 . "AcDbLine") (10 16602.5622624434
920.0594117647 0.0) (11 16602.5622624434 939.0686877828 0.0))
((0 . "LINE") (100 . "AcDbEntity") (8 . "MASONRY") (62 . 7) (370 . 13) (100 . "AcDbLine") (10 16889.1402714932
939.0686877828 0.0) (11 16602.5622624434 939.0686877828 0.0))
((0 . "LINE") (100 . "AcDbEntity") (8 . "MASONRY") (62 . 7) (370 . 13) (100 . "AcDbLine") (10 16602.5622624434
886.1241402715 0.0) (11 16610.1074208145 886.1241402715 0.0))
((0 . "LINE") (100 . "AcDbEntity") (8 . "MASONRY") (62 . 7) (370 . 13) (100 . "AcDbLine") (10 16613.874479638
2036.1990950226 0.0) (11 16644.0440723982 2036.1990950226 0.0))
((0 . "LINE") (100 . "AcDbEntity") (8 . "MASONRY") (62 . 7) (370 . 13) (100 . "AcDbLine") (10 16651.5837104072
2105.9573076923 0.0) (11 16621.4196380091 2105.9573076923 0.0))
((0 . "LINE") (100 . "AcDbEntity") (8 . "MASONRY") (62 . 7) (370 . 13) (100 . "AcDbLine") (10 16628.9592760181
1285.8229411765 0.0) (11 16659.1233484163 1285.8229411765 0.0))
((0 . "LINE") (100 . "AcDbEntity") (8 . "MASONRY") (62 . 7) (370 . 13) (100 . "AcDbLine") (10 16870.2884162896
1955.1286651584 0.0) (11 16632.7318552036 1955.1286651584 0.0))
((0 . "LINE") (100 . "AcDbEntity") (8 . "MASONRY") (62 . 7) (370 . 13) (100 . "AcDbLine") (10 16713.8009049774
1862.822658371 0.0) (11 16634.6153846154 1862.822658371 0.0))
((0 . "LINE") (100 . "AcDbEntity") (8 . "MASONRY") (62 . 7) (370 . 13) (100 . "AcDbLine") (10 16634.6153846154
1877.8280542986 0.0) (11 16634.6153846154 1862.822658371 0.0))
((0 . "LINE") (100 . "AcDbEntity") (8 . "MASONRY") (62 . 7) (370 . 13) (100 . "AcDbLine") (10 16632.7318552036
1434.7666742081 0.0) (11 17009.802081448 1434.7666742081 0.0))
((0 . "LINE") (100 . "AcDbEntity") (8 . "MASONRY") (62 . 7) (370 . 13) (100 . "AcDbLine") (10 16776.0180995475
3256.1848529412 0.0) (11 16749.6210859729 3256.1848529412 0.0))
((0 . "LINE") (100 . "AcDbEntity") (8 . "MASONRY") (62 . 7) (370 . 13) (100 . "AcDbLine") (10 16749.6210859729
3256.1848529412 0.0) (11 16651.5837104072 3256.1848529412 0.0))
((0 . "LINE") (100 . "AcDbEntity") (8 . "MASONRY") (62 . 7) (370 . 13) (100 . "AcDbLine") (10 16892.9128506787
2509.4273076923 0.0) (11 16651.5837104072 2509.4273076923 0.0))
((0 . "LINE") (100 . "AcDbEntity") (8 . "MASONRY") (62 . 7) (370 . 13) (100 . "AcDbLine") (10 16653.47 1685.520361991
0.0) (11 16653.47 1696.8325791855 0.0))
((0 . "LINE") (100 . "AcDbEntity") (8 . "MASONRY") (62 . 7) (370 . 13) (100 . "AcDbLine") (10 16653.47 1640.2714932127
0.0) (11 16653.47 1600.6787330317 0.0))
((0 . "LINE") (100 . "AcDbEntity") (8 . "MASONRY") (62 . 7) (370 . 13) (100 . "AcDbLine") (10 16892.9128506787
3050.5281334842 0.0) (11 16655.3562895928 3050.5281334842 0.0))
((0 . "LINE") (100 . "AcDbEntity") (8 . "MASONRY") (62 . 7) (370 . 13) (100 . "AcDbLine") (10 16674.2081447964
2779.0349208145 0.0) (11 16655.3562895928 2779.0349208145 0.0))
((0 . "LINE") (100 . "AcDbEntity") (8 . "MASONRY") (62 . 7) (370 . 13) (100 . "AcDbLine") (10 16670.4355656109
1685.520361991 0.0) (11 16653.47 1685.520361991 0.0))
((0 . "LINE") (100 . "AcDbEntity") (8 . "MASONRY") (62 . 7) (370 . 13) (100 . "AcDbLine") (10 16804.2986425339
1600.6787330317 0.0) (11 16653.47 1600.6787330317 0.0))
((0 . "LINE") (100 . "AcDbEntity") (8 . "MASONRY") (62 . 7) (370 . 13) (100 . "AcDbLine") (10 16659.1233484163
3514.3290384615 0.0) (11 16813.7273303167 3514.3290384615 0.0))
((0 . "LINE") (100 . "AcDbEntity") (8 . "MASONRY") (62 . 7) (370 . 13) (100 . "AcDbLine") (10 16659.1233484163
3340.874581448 0.0) (11 16687.4066515837 3340.874581448 0.0))
((0 . "LINE") (100 . "AcDbEntity") (8 . "MASONRY") (62 . 7) (370 . 13) (100 . "AcDbLine") (10 16691.1764705882
3107.089219457 0.0) (11 16659.1233484163 3107.089219457 0.0))
((0 . "LINE") (100 . "AcDbEntity") (8 . "MASONRY") (62 . 7) (370 . 13) (100 . "AcDbLine") (10 16659.1233484163
2895.92760181 0.0) (11 16870.2884162896 2895.92760181 0.0))
((0 . "LINE") (100 . "AcDbEntity") (8 . "MASONRY") (62 . 7) (370 . 13) (100 . "AcDbLine") (10 17130.4694117647
3182.799739819 0.0) (11 16806.1821719457 3182.799739819 0.0))
((0 . "LINE") (100 . "AcDbEntity") (8 . "MASONRY") (62 . 7) (370 . 13) (100 . "AcDbLine") (10 16806.1821719457
3182.799739819 0.0) (11 16715.6844343891 3182.799739819 0.0))
((0 . "LINE") (100 . "AcDbEntity") (8 . "MASONRY") (62 . 7) (370 . 13) (100 . "AcDbLine") (10 16715.6844343891
3182.799739819 0.0) (11 16666.6657466063 3182.799739819 0.0))
((0 . "LINE") (100 . "AcDbEntity") (8 . "MASONRY") (62 . 7) (370 . 13) (100 . "AcDbLine") (10 16666.6657466063
3182.799739819 0.0) (11 16666.6657466063 3159.8791063348 0.0))
((0 . "LINE") (100 . "AcDbEntity") (8 . "MASONRY") (62 . 7) (370 . 13) (100 . "AcDbLine") (10 16664.9672511312
2609.3516628959 0.0) (11 16664.9672511312 2633.8616968326 0.0))
((0 . "LINE") (100 . "AcDbEntity") (8 . "MASONRY") (62 . 7) (370 . 13) (100 . "AcDbLine") (10 16664.9672511312
2633.8616968326 0.0) (11 16870.2884162896 2633.8616968326 0.0))
((0 . "LINE") (100 . "AcDbEntity") (8 . "MASONRY") (62 . 7) (370 . 13) (100 . "AcDbLine") (10 16666.6685067873
2317.1196153846 0.0) (11 16666.6685067873 2352.9411764706 0.0))
((0 . "LINE") (100 . "AcDbEntity") (8 . "MASONRY") (62 . 7) (370 . 13) (100 . "AcDbLine") (10 16666.6685067873
2317.1196153846 0.0) (11 16704.3722171946 2317.1196153846 0.0))
((0 . "LINE") (100 . "AcDbEntity") (8 . "MASONRY") (62 . 7) (370 . 13) (100 . "AcDbLine") (10 16674.2081447964
2801.6593552036 0.0) (11 16674.2081447964 2779.0349208145 0.0))
((0 . "LINE") (100 . "AcDbEntity") (8 . "MASONRY") (62 . 7) (370 . 13) (100 . "AcDbLine") (10 16670.4355656109
1123.679321267 0.0) (11 16738.3088687783 1123.679321267 0.0))
((0 . "LINE") (100 . "AcDbEntity") (8 . "MASONRY") (62 . 7) (370 . 13) (100 . "AcDbLine") (10 16674.2081447964
2858.2204411765 0.0) (11 16674.2081447964 2824.2837895928 0.0))
((0 . "LINE") (100 . "AcDbEntity") (8 . "MASONRY") (62 . 7) (370 . 13) (100 . "AcDbLine") (10 16674.2081447964
2424.5849886878 0.0) (11 16674.2081447964 2413.2727714932 0.0))
((0 . "LINE") (100 . "AcDbEntity") (8 . "MASONRY") (62 . 7) (370 . 13) (100 . "AcDbLine") (10 16766.5921719457
2424.5849886878 0.0) (11 16674.2081447964 2424.5849886878 0.0))
((0 . "LINE") (100 . "AcDbEntity") (8 . "MASONRY") (62 . 7) (370 . 13) (100 . "AcDbLine") (10 16794.8699547511
2041.8552036199 0.0) (11 16674.2081447964 2041.8552036199 0.0))
((0 . "LINE") (100 . "AcDbEntity") (8 . "MASONRY") (62 . 7) (370 . 13) (100 . "AcDbLine") (10 16674.2081447964
2779.0349208145 0.0) (11 16868.4021266968 2779.0349208145 0.0))
((0 . "LINE") (100 . "AcDbEntity") (8 . "MASONRY") (62 . 7) (370 . 13) (100 . "AcDbLine") (10 16685.520361991
1287.7078506787 0.0) (11 16677.9807239819 1287.7078506787 0.0))
((0 . "LINE") (100 . "AcDbEntity") (8 . "MASONRY") (62 . 7) (370 . 13) (100 . "AcDbLine") (10 16687.4066515837
3340.874581448 0.0) (11 16828.8066063348 3340.874581448 0.0))
((0 . "LINE") (100 . "AcDbEntity") (8 . "MASONRY") (62 . 7) (370 . 13) (100 . "AcDbLine") (10 16687.4066515837
3340.874581448 0.0) (11 16687.4066515837 3371.0407239819 0.0))
((0 . "LINE") (100 . "AcDbEntity") (8 . "MASONRY") (62 . 7) (370 . 13) (100 . "AcDbLine") (10 16685.520361991
2109.7285067873 0.0) (11 16719.4570135747 2109.7285067873 0.0))
((0 . "LINE") (100 . "AcDbEntity") (8 . "MASONRY") (62 . 7) (370 . 13) (100 . "AcDbLine") (10 16804.0003733032
651.537861991 0.0) (11 16862.4753619909 651.537861991 0.0))
((0 . "LINE") (100 . "AcDbEntity") (8 . "MASONRY") (62 . 7) (370 . 13) (100 . "AcDbLine") (10 16691.1764705882
3469.0801696833 0.0) (11 16691.1764705882 3442.6845361991 0.0))
((0 . "LINE") (100 . "AcDbEntity") (8 . "MASONRY") (62 . 7) (370 . 13) (100 . "AcDbLine") (10 16691.1764705882
3092.0058031674 0.0) (11 16691.1764705882 3107.089219457 0.0))
((0 . "LINE") (100 . "AcDbEntity") (8 . "MASONRY") (62 . 7) (370 . 13) (100 . "AcDbLine") (10 16691.1764705882
3469.0801696833 0.0) (11 16874.0554751131 3469.0801696833 0.0))
((0 . "LINE") (100 . "AcDbEntity") (8 . "MASONRY") (62 . 7) (370 . 13) (100 . "AcDbLine") (10 16768.4784615385
3107.089219457 0.0) (11 16691.1764705882 3107.089219457 0.0))
((0 . "LINE") (100 . "AcDbEntity") (8 . "MASONRY") (62 . 7) (370 . 13) (100 . "AcDbLine") (10 16693.06 1165.1583710407
0.0) (11 16693.06 1180.2404072398 0.0))
((0 . "LINE") (100 . "AcDbEntity") (8 . "MASONRY") (62 . 7) (370 . 13) (100 . "AcDbLine") (10 16693.06 1180.2404072398
0.0) (11 16874.0554751131 1180.2404072398 0.0))
((0 . "LINE") (100 . "AcDbEntity") (8 . "MASONRY") (62 . 7) (370 . 13) (100 . "AcDbLine") (10 16704.3722171946
2190.1975565611 0.0) (11 16704.3722171946 2263.6524095023 0.0))
((0 . "LINE") (100 . "AcDbEntity") (8 . "MASONRY") (62 . 7) (370 . 13) (100 . "AcDbLine") (10 16704.3722171946
2317.1196153846 0.0) (11 16704.3722171946 2263.6524095023 0.0))
((0 . "LINE") (100 . "AcDbEntity") (8 . "MASONRY") (62 . 7) (370 . 13) (100 . "AcDbLine") (10 16696.8325791855
1248.1150904977 0.0) (11 16825.0395475113 1248.1150904977 0.0))
((0 . "LINE") (100 . "AcDbEntity") (8 . "MASONRY") (62 . 7) (370 . 13) (100 . "AcDbLine") (10 16704.3722171946
2190.1975565611 0.0) (11 16710.0310859729 2190.1975565611 0.0))
((0 . "LINE") (100 . "AcDbEntity") (8 . "MASONRY") (62 . 7) (370 . 13) (100 . "AcDbLine") (10 16704.3722171946
1691.1764705882 0.0) (11 16730.7692307692 1691.1764705882 0.0))
((0 . "LINE") (100 . "AcDbEntity") (8 . "MASONRY") (62 . 7) (370 . 13) (100 . "AcDbLine") (10 17179.4853393665
2317.1196153846 0.0) (11 16704.3722171946 2317.1196153846 0.0))
((0 . "LINE") (100 . "AcDbEntity") (8 . "MASONRY") (62 . 7) (370 . 13) (100 . "AcDbLine") (10 16710.0310859729
2190.1975565611 0.0) (11 16710.0310859729 2171.9457013575 0.0))
((0 . "LINE") (100 . "AcDbEntity") (8 . "MASONRY") (62 . 7) (370 . 13) (100 . "AcDbLine") (10 16909.8784162896
2190.1975565611 0.0) (11 16710.0310859729 2190.1975565611 0.0))
((0 . "LINE") (100 . "AcDbEntity") (8 . "MASONRY") (62 . 7) (370 . 13) (100 . "AcDbLine") (10 16745.8540271493
1461.1609276018 0.0) (11 16711.9173755656 1461.1609276018 0.0))
((0 . "LINE") (100 . "AcDbEntity") (8 . "MASONRY") (62 . 7) (370 . 13) (100 . "AcDbLine") (10 16715.6844343891
2826.1693891403 0.0) (11 16742.0814479638 2826.1693891403 0.0))
((0 . "LINE") (100 . "AcDbEntity") (8 . "MASONRY") (62 . 7) (370 . 13) (100 . "AcDbLine") (10 16713.8009049774
1862.822658371 0.0) (11 16734.5418099548 1862.822658371 0.0))
((0 . "LINE") (100 . "AcDbEntity") (8 . "MASONRY") (62 . 7) (370 . 13) (100 . "AcDbLine") (10 16868.4021266968
2109.7285067873 0.0) (11 16753.3936651584 2109.7285067873 0.0))
((0 . "LINE") (100 . "AcDbEntity") (8 . "MASONRY") (62 . 7) (370 . 13) (100 . "AcDbLine") (10 16755.8074547511
1040.7239819005 0.0) (11 16755.8074547511 1001.1312217195 0.0))
((0 . "LINE") (100 . "AcDbEntity") (8 . "MASONRY") (62 . 7) (370 . 13) (100 . "AcDbLine") (10 16755.8074547511
1001.1312217195 0.0) (11 16783.5577375566 1001.1312217195 0.0))
((0 . "LINE") (100 . "AcDbEntity") (8 . "MASONRY") (62 . 7) (370 . 13) (100 . "AcDbLine") (10 16941.9287782805
1862.7453280543 0.0) (11 16760.9333031674 1862.7453280543 0.0))
((0 . "LINE") (100 . "AcDbEntity") (8 . "MASONRY") (62 . 7) (370 . 13) (100 . "AcDbLine") (10 16763.8359276018
723.9819004525 0.0) (11 16806.1807918552 723.9819004525 0.0))
((0 . "LINE") (100 . "AcDbEntity") (8 . "MASONRY") (62 . 7) (370 . 13) (100 . "AcDbLine") (10 16766.5921719457
2424.5849886878 0.0) (11 16776.0180995475 2424.5849886878 0.0))
((0 . "LINE") (100 . "AcDbEntity") (8 . "MASONRY") (62 . 7) (370 . 13) (100 . "AcDbLine") (10 16776.0180995475
2424.5849886878 0.0) (11 16836.3517647059 2424.5849886878 0.0))
((0 . "LINE") (100 . "AcDbEntity") (8 . "MASONRY") (62 . 7) (370 . 13) (100 . "AcDbLine") (10 16766.5921719457
2424.5849886878 0.0) (11 16766.5921719457 2435.8972058824 0.0))
((0 . "LINE") (100 . "AcDbEntity") (8 . "MASONRY") (62 . 7) (370 . 13) (100 . "AcDbLine") (10 16772.245520362
769.1817533937 0.0) (11 16928.5811312217 769.1817533937 0.0))
((0 . "LINE") (100 . "AcDbEntity") (8 . "MASONRY") (62 . 7) (370 . 13) (100 . "AcDbLine") (10 16968.3257918552
772.8604298643 0.0) (11 17011.6869909502 772.8604298643 0.0))
((0 . "LINE") (100 . "AcDbEntity") (8 . "MASONRY") (62 . 7) (370 . 13) (100 . "AcDbLine") (10 17011.6869909502
772.8604298643 0.0) (11 17011.6869909502 727.751719457 0.0))
((0 . "LINE") (100 . "AcDbEntity") (8 . "MASONRY") (62 . 7) (370 . 13) (100 . "AcDbLine") (10 16776.0180995475
3299.3969117647 0.0) (11 16776.0180995475 3256.1848529412 0.0))
((0 . "LINE") (100 . "AcDbEntity") (8 . "MASONRY") (62 . 7) (370 . 13) (100 . "AcDbLine") (10 17006.0350226244
3256.1848529412 0.0) (11 16776.0180995475 3256.1848529412 0.0))
((0 . "LINE") (100 . "AcDbEntity") (8 . "MASONRY") (62 . 7) (370 . 13) (100 . "AcDbLine") (10 16806.1807918552
723.9819004525 0.0) (11 16806.1807918552 701.4347963801 0.0))
((0 . "LINE") (100 . "AcDbEntity") (8 . "MASONRY") (62 . 7) (370 . 13) (100 . "AcDbLine") (10 16806.1807918552
701.4347963801 0.0) (11 16779.790678733 701.4347963801 0.0))
((0 . "LINE") (100 . "AcDbEntity") (8 . "MASONRY") (62 . 7) (370 . 13) (100 . "AcDbLine") (10 16847.6639819005
2558.4459954751 0.0) (11 16783.5577375566 2558.4459954751 0.0))
((0 . "LINE") (100 . "AcDbEntity") (8 . "MASONRY") (62 . 7) (370 . 13) (100 . "AcDbLine") (10 16792.9864253394
2956.2591968326 0.0) (11 16792.9864253394 2948.718178733 0.0))
((0 . "LINE") (100 . "AcDbEntity") (8 . "MASONRY") (62 . 7) (370 . 13) (100 . "AcDbLine") (10 16817.4943891403
827.6767647059 0.0) (11 16791.1028959276 827.6767647059 0.0))
((0 . "LINE") (100 . "AcDbEntity") (8 . "MASONRY") (62 . 7) (370 . 13) (100 . "AcDbLine") (10 16821.2669683258
3103.318020362 0.0) (11 16798.6425339367 3103.318020362 0.0))
((0 . "LINE") (100 . "AcDbEntity") (8 . "MASONRY") (62 . 7) (370 . 13) (100 . "AcDbLine") (10 16968.3257918552
1681.7505429864 0.0) (11 16813.7273303167 1681.7505429864 0.0))
((0 . "LINE") (100 . "AcDbEntity") (8 . "MASONRY") (62 . 7) (370 . 13) (100 . "AcDbLine") (10 16813.7273303167
1681.7505429864 0.0) (11 16799.2446040724 1681.7505429864 0.0))
((0 . "LINE") (100 . "AcDbEntity") (8 . "MASONRY") (62 . 7) (370 . 13) (100 . "AcDbLine") (10 16799.2446040724
1681.7505429864 0.0) (11 16799.2446040724 1708.1447963801 0.0))
((0 . "LINE") (100 . "AcDbEntity") (8 . "MASONRY") (62 . 7) (370 . 13) (100 . "AcDbLine") (10 16804.2986425339
1600.6787330317 0.0) (11 16804.2986425339 1640.2714932127 0.0))
((0 . "LINE") (100 . "AcDbEntity") (8 . "MASONRY") (62 . 7) (370 . 13) (100 . "AcDbLine") (10 16889.1402714932
991.7052941176 0.0) (11 16802.4151131222 991.7052941176 0.0))
((0 . "LINE") (100 . "AcDbEntity") (8 . "MASONRY") (62 . 7) (370 . 13) (100 . "AcDbLine") (10 16804.2986425339
1600.6787330317 0.0) (11 16817.4943891403 1600.6787330317 0.0))
((0 . "LINE") (100 . "AcDbEntity") (8 . "MASONRY") (62 . 7) (370 . 13) (100 . "AcDbLine") (10 16832.5791855204
2958.1447963801 0.0) (11 16809.9547511312 2958.1447963801 0.0))
((0 . "LINE") (100 . "AcDbEntity") (8 . "MASONRY") (62 . 7) (370 . 13) (100 . "AcDbLine") (10 16809.9547511312
2441.5540045249 0.0) (11 16825.0395475113 2441.5540045249 0.0))
((0 . "LINE") (100 . "AcDbEntity") (8 . "MASONRY") (62 . 7) (370 . 13) (100 . "AcDbLine") (10 16855.2036199095
723.9819004525 0.0) (11 16806.1807918552 723.9819004525 0.0))
((0 . "LINE") (100 . "AcDbEntity") (8 . "MASONRY") (62 . 7) (370 . 13) (100 . "AcDbLine") (10 16825.0395475113
2045.6264027149 0.0) (11 16870.2884162896 2045.6264027149 0.0))
((0 . "LINE") (100 . "AcDbEntity") (8 . "MASONRY") (62 . 7) (370 . 13) (100 . "AcDbLine") (10 16825.0395475113
1815.6108597285 0.0) (11 17024.8868778281 1815.6108597285 0.0))
((0 . "LINE") (100 . "AcDbEntity") (8 . "MASONRY") (62 . 7) (370 . 13) (100 . "AcDbLine") (10 16866.5158371041
1541.0341289593 0.0) (11 16866.5158371041 1466.8916063348 0.0))
((0 . "LINE") (100 . "AcDbEntity") (8 . "MASONRY") (62 . 7) (370 . 13) (100 . "AcDbLine") (10 16866.5158371041
1466.8916063348 0.0) (11 16832.5791855204 1466.8916063348 0.0))
((0 . "LINE") (100 . "AcDbEntity") (8 . "MASONRY") (62 . 7) (370 . 13) (100 . "AcDbLine") (10 16855.2036199095
3101.4324208145 0.0) (11 16911.7647058824 3101.4324208145 0.0))
((0 . "LINE") (100 . "AcDbEntity") (8 . "MASONRY") (62 . 7) (370 . 13) (100 . "AcDbLine") (10 16870.2884162896
2969.4570135747 0.0) (11 16870.2884162896 2956.2591968326 0.0))
((0 . "LINE") (100 . "AcDbEntity") (8 . "MASONRY") (62 . 7) (370 . 13) (100 . "AcDbLine") (10 17162.5197737557
3469.0801696833 0.0) (11 16874.0554751131 3469.0801696833 0.0))
((0 . "LINE") (100 . "AcDbEntity") (8 . "MASONRY") (62 . 7) (370 . 13) (100 . "AcDbLine") (10 16874.0554751131
3525.6412556561 0.0) (11 16874.0554751131 3469.0801696833 0.0))
((0 . "LINE") (100 . "AcDbEntity") (8 . "MASONRY") (62 . 7) (370 . 13) (100 . "AcDbLine") (10 16868.4021266968
2779.0349208145 0.0) (11 17175.718280543 2779.0349208145 0.0))
((0 . "LINE") (100 . "AcDbEntity") (8 . "MASONRY") (62 . 7) (370 . 13) (100 . "AcDbLine") (10 16868.4021266968
2760.1809954751 0.0) (11 16868.4021266968 2779.0349208145 0.0))
((0 . "LINE") (100 . "AcDbEntity") (8 . "MASONRY") (62 . 7) (370 . 13) (100 . "AcDbLine") (10 16870.2884162896
2633.8616968326 0.0) (11 16894.7963800905 2633.8616968326 0.0))
((0 . "LINE") (100 . "AcDbEntity") (8 . "MASONRY") (62 . 7) (370 . 13) (100 . "AcDbLine") (10 16870.2884162896
2633.8616968326 0.0) (11 16870.2884162896 2718.7033257919 0.0))
((0 . "LINE") (100 . "AcDbEntity") (8 . "MASONRY") (62 . 7) (370 . 13) (100 . "AcDbLine") (10 16868.4021266968
2070.1357466063 0.0) (11 16868.4021266968 2109.7285067873 0.0))
((0 . "LINE") (100 . "AcDbEntity") (8 . "MASONRY") (62 . 7) (370 . 13) (100 . "AcDbLine") (10 16868.4021266968
2109.7285067873 0.0) (11 16909.8784162896 2109.7285067873 0.0))
((0 . "LINE") (100 . "AcDbEntity") (8 . "MASONRY") (62 . 7) (370 . 13) (100 . "AcDbLine") (10 16870.2884162896
2011.6897511312 0.0) (11 16870.2884162896 2045.6264027149 0.0))
((0 . "LINE") (100 . "AcDbEntity") (8 . "MASONRY") (62 . 7) (370 . 13) (100 . "AcDbLine") (10 16870.2884162896
2045.6264027149 0.0) (11 16870.2884162896 2058.8235294118 0.0))
((0 . "LINE") (100 . "AcDbEntity") (8 . "MASONRY") (62 . 7) (370 . 13) (100 . "AcDbLine") (10 16866.5158371041
1541.0341289593 0.0) (11 16866.5158371041 1594.9121493213 0.0))
((0 . "LINE") (100 . "AcDbEntity") (8 . "MASONRY") (62 . 7) (370 . 13) (100 . "AcDbLine") (10 16866.5158371041
1594.9121493213 0.0) (11 16957.0135746606 1594.9121493213 0.0))
((0 . "LINE") (100 . "AcDbEntity") (8 . "MASONRY") (62 . 7) (370 . 13) (100 . "AcDbLine") (10 16874.0554751131
1255.6561085973 0.0) (11 16874.0554751131 1236.8028733032 0.0))
((0 . "LINE") (100 . "AcDbEntity") (8 . "MASONRY") (62 . 7) (370 . 13) (100 . "AcDbLine") (10 16889.1402714932
3342.7601809955 0.0) (11 16870.2884162896 3342.7601809955 0.0))
((0 . "LINE") (100 . "AcDbEntity") (8 . "MASONRY") (62 . 7) (370 . 13) (100 . "AcDbLine") (10 16870.2884162896
2969.4570135747 0.0) (11 16870.2884162896 3001.5080656109 0.0))
((0 . "LINE") (100 . "AcDbEntity") (8 . "MASONRY") (62 . 7) (370 . 13) (100 . "AcDbLine") (10 17183.257918552
2969.4570135747 0.0) (11 16870.2884162896 2969.4570135747 0.0))
((0 . "LINE") (100 . "AcDbEntity") (8 . "MASONRY") (62 . 7) (370 . 13) (100 . "AcDbLine") (10 16870.2884162896
2922.3225452489 0.0) (11 16870.2884162896 2895.92760181 0.0))
((0 . "LINE") (100 . "AcDbEntity") (8 . "MASONRY") (62 . 7) (370 . 13) (100 . "AcDbLine") (10 17179.4853393665
2895.92760181 0.0) (11 16870.2884162896 2895.92760181 0.0))
((0 . "LINE") (100 . "AcDbEntity") (8 . "MASONRY") (62 . 7) (370 . 13) (100 . "AcDbLine") (10 16949.4739366516
2718.7033257919 0.0) (11 16870.2884162896 2718.7033257919 0.0))
((0 . "LINE") (100 . "AcDbEntity") (8 . "MASONRY") (62 . 7) (370 . 13) (100 . "AcDbLine") (10 16870.2884162896
2558.4459954751 0.0) (11 16892.9128506787 2558.4459954751 0.0))
((0 . "LINE") (100 . "AcDbEntity") (8 . "MASONRY") (62 . 7) (370 . 13) (100 . "AcDbLine") (10 16881.5978733032
2418.9295701357 0.0) (11 16870.2884162896 2418.9295701357 0.0))
((0 . "LINE") (100 . "AcDbEntity") (8 . "MASONRY") (62 . 7) (370 . 13) (100 . "AcDbLine") (10 16870.2884162896
2011.6897511312 0.0) (11 16885.3676923077 2011.6897511312 0.0))
((0 . "LINE") (100 . "AcDbEntity") (8 . "MASONRY") (62 . 7) (370 . 13) (100 . "AcDbLine") (10 16870.2884162896
2011.6897511312 0.0) (11 16870.2884162896 1987.1797171946 0.0))
((0 . "LINE") (100 . "AcDbEntity") (8 . "MASONRY") (62 . 7) (370 . 13) (100 . "AcDbLine") (10 16870.2884162896
1955.1286651584 0.0) (11 16870.2884162896 1968.3257918552 0.0))
((0 . "LINE") (100 . "AcDbEntity") (8 . "MASONRY") (62 . 7) (370 . 13) (100 . "AcDbLine") (10 16870.2884162896
1955.1286651584 0.0) (11 16987.1776470588 1955.1286651584 0.0))
((0 . "LINE") (100 . "AcDbEntity") (8 . "MASONRY") (62 . 7) (370 . 13) (100 . "AcDbLine") (10 16874.6603054299
829.5616742081 0.0) (11 16874.6603054299 901.0522058824 0.0))
((0 . "LINE") (100 . "AcDbEntity") (8 . "MASONRY") (62 . 7) (370 . 13) (100 . "AcDbLine") (10 16874.6603054299
901.0522058824 0.0) (11 16892.9128506787 901.0522058824 0.0))
((0 . "LINE") (100 . "AcDbEntity") (8 . "MASONRY") (62 . 7) (370 . 13) (100 . "AcDbLine") (10 16892.9128506787
901.0522058824 0.0) (11 16941.9287782805 901.0522058824 0.0))
((0 . "LINE") (100 . "AcDbEntity") (8 . "MASONRY") (62 . 7) (370 . 13) (100 . "AcDbLine") (10 16874.0554751131
3525.6412556561 0.0) (11 16874.0554751131 3536.9534728507 0.0))
((0 . "LINE") (100 . "AcDbEntity") (8 . "MASONRY") (62 . 7) (370 . 13) (100 . "AcDbLine") (10 16881.5978733032
2418.9295701357 0.0) (11 16881.5978733032 2439.6684049774 0.0))
((0 . "LINE") (100 . "AcDbEntity") (8 . "MASONRY") (62 . 7) (370 . 13) (100 . "AcDbLine") (10 17183.257918552
1322.1720022624 0.0) (11 16949.4739366516 1322.1720022624 0.0))
((0 . "LINE") (100 . "AcDbEntity") (8 . "MASONRY") (62 . 7) (370 . 13) (100 . "AcDbLine") (10 16949.4739366516
1322.1720022624 0.0) (11 16911.7647058824 1322.1720022624 0.0))
((0 . "LINE") (100 . "AcDbEntity") (8 . "MASONRY") (62 . 7) (370 . 13) (100 . "AcDbLine") (10 16911.7647058824
1322.1720022624 0.0) (11 16876.0190950226 1322.1720022624 0.0))
((0 . "LINE") (100 . "AcDbEntity") (8 . "MASONRY") (62 . 7) (370 . 13) (100 . "AcDbLine") (10 16876.0190950226
1322.1720022624 0.0) (11 16876.0190950226 1331.0718099548 0.0))
((0 . "LINE") (100 . "AcDbEntity") (8 . "MASONRY") (62 . 7) (370 . 13) (100 . "AcDbLine") (10 16881.6006334842
1331.0718099548 0.0) (11 16876.0190950226 1331.0718099548 0.0))
((0 . "LINE") (100 . "AcDbEntity") (8 . "MASONRY") (62 . 7) (370 . 13) (100 . "AcDbLine") (10 17179.4853393665
1180.2404072398 0.0) (11 16874.0554751131 1180.2404072398 0.0))
((0 . "LINE") (100 . "AcDbEntity") (8 . "MASONRY") (62 . 7) (370 . 13) (100 . "AcDbLine") (10 16874.0554751131
1236.8028733032 0.0) (11 16874.0554751131 1180.2404072398 0.0))
((0 . "LINE") (100 . "AcDbEntity") (8 . "MASONRY") (62 . 7) (370 . 13) (100 . "AcDbLine") (10 17183.257918552
3525.6412556561 0.0) (11 16874.0554751131 3525.6412556561 0.0))
((0 . "LINE") (100 . "AcDbEntity") (8 . "MASONRY") (62 . 7) (370 . 13) (100 . "AcDbLine") (10 16874.0554751131
1236.8028733032 0.0) (11 17183.257918552 1236.8028733032 0.0))
((0 . "LINE") (100 . "AcDbEntity") (8 . "MASONRY") (62 . 7) (370 . 13) (100 . "AcDbLine") (10 16881.5978733032
2418.9295701357 0.0) (11 17011.6938914027 2418.9295701357 0.0))
((0 . "LINE") (100 . "AcDbEntity") (8 . "MASONRY") (62 . 7) (370 . 13) (100 . "AcDbLine") (10 16889.1402714932
939.0686877828 0.0) (11 16889.1402714932 991.7052941176 0.0))
((0 . "LINE") (100 . "AcDbEntity") (8 . "MASONRY") (62 . 7) (370 . 13) (100 . "AcDbLine") (10 16896.6799095023
991.7052941176 0.0) (11 16889.1402714932 991.7052941176 0.0))
((0 . "LINE") (100 . "AcDbEntity") (8 . "MASONRY") (62 . 7) (370 . 13) (100 . "AcDbLine") (10 16889.1402714932
939.0686877828 0.0) (11 16943.7101244344 939.0686877828 0.0))
((0 . "LINE") (100 . "AcDbEntity") (8 . "MASONRY") (62 . 7) (370 . 13) (100 . "AcDbLine") (10 16943.7101244344
939.0686877828 0.0) (11 16943.7101244344 987.8567647059 0.0))
((0 . "LINE") (100 . "AcDbEntity") (8 . "MASONRY") (62 . 7) (370 . 13) (100 . "AcDbLine") (10 16943.7101244344
987.8567647059 0.0) (11 17179.4853393665 987.8567647059 0.0))
((0 . "LINE") (100 . "AcDbEntity") (8 . "MASONRY") (62 . 7) (370 . 13) (100 . "AcDbLine") (10 16891.6286312217
3427.6018099548 0.0) (11 16891.6286312217 3386.1269004525 0.0))
((0 . "LINE") (100 . "AcDbEntity") (8 . "MASONRY") (62 . 7) (370 . 13) (100 . "AcDbLine") (10 16891.6286312217
3386.1269004525 0.0) (11 16911.7647058824 3386.1269004525 0.0))
((0 . "LINE") (100 . "AcDbEntity") (8 . "MASONRY") (62 . 7) (370 . 13) (100 . "AcDbLine") (10 16894.7963800905
2594.2682466063 0.0) (11 16894.7963800905 2633.8616968326 0.0))
((0 . "LINE") (100 . "AcDbEntity") (8 . "MASONRY") (62 . 7) (370 . 13) (100 . "AcDbLine") (10 16892.9128506787
2537.7071606335 0.0) (11 16892.9128506787 2509.4273076923 0.0))
((0 . "LINE") (100 . "AcDbEntity") (8 . "MASONRY") (62 . 7) (370 . 13) (100 . "AcDbLine") (10 17007.9185520362
2509.4273076923 0.0) (11 16892.9128506787 2509.4273076923 0.0))
((0 . "LINE") (100 . "AcDbEntity") (8 . "MASONRY") (62 . 7) (370 . 13) (100 . "AcDbLine") (10 16904.2250678733
2633.8616968326 0.0) (11 16894.7963800905 2633.8616968326 0.0))
((0 . "LINE") (100 . "AcDbEntity") (8 . "MASONRY") (62 . 7) (370 . 13) (100 . "AcDbLine") (10 16909.8784162896
2190.1975565611 0.0) (11 16909.8784162896 2109.7285067873 0.0))
((0 . "LINE") (100 . "AcDbEntity") (8 . "MASONRY") (62 . 7) (370 . 13) (100 . "AcDbLine") (10 16909.8784162896
2190.1975565611 0.0) (11 16981.5242986425 2190.1975565611 0.0))
((0 . "LINE") (100 . "AcDbEntity") (8 . "MASONRY") (62 . 7) (370 . 13) (100 . "AcDbLine") (10 16909.8784162896
2109.7285067873 0.0) (11 17179.4853393665 2109.7285067873 0.0))
((0 . "LINE") (100 . "AcDbEntity") (8 . "MASONRY") (62 . 7) (370 . 13) (100 . "AcDbLine") (10 16923.0769230769
3376.6968325792 0.0) (11 17066.3631674208 3376.6968325792 0.0))
((0 . "LINE") (100 . "AcDbEntity") (8 . "MASONRY") (62 . 7) (370 . 13) (100 . "AcDbLine") (10 16923.0769230769
3103.318020362 0.0) (11 16979.6380090498 3103.318020362 0.0))
((0 . "LINE") (100 . "AcDbEntity") (8 . "MASONRY") (62 . 7) (370 . 13) (100 . "AcDbLine") (10 17006.0350226244
3337.1040723982 0.0) (11 16926.8495022624 3337.1040723982 0.0))
((0 . "LINE") (100 . "AcDbEntity") (8 . "MASONRY") (62 . 7) (370 . 13) (100 . "AcDbLine") (10 17028.6594570136
3050.5281334842 0.0) (11 16930.616561086 3050.5281334842 0.0))
((0 . "LINE") (100 . "AcDbEntity") (8 . "MASONRY") (62 . 7) (370 . 13) (100 . "AcDbLine") (10 16945.7013574661
2631.9760972851 0.0) (11 17039.9716742081 2631.9760972851 0.0))
((0 . "LINE") (100 . "AcDbEntity") (8 . "MASONRY") (62 . 7) (370 . 13) (100 . "AcDbLine") (10 17036.1990950226
2607.4660633484 0.0) (11 16949.4739366516 2607.4660633484 0.0))
((0 . "LINE") (100 . "AcDbEntity") (8 . "MASONRY") (62 . 7) (370 . 13) (100 . "AcDbLine") (10 17011.6869909502
727.751719457 0.0) (11 16968.3257918552 727.751719457 0.0))
((0 . "LINE") (100 . "AcDbEntity") (8 . "MASONRY") (62 . 7) (370 . 13) (100 . "AcDbLine") (10 16957.0135746606
1594.9121493213 0.0) (11 16957.0135746606 1628.9592760181 0.0))
((0 . "LINE") (100 . "AcDbEntity") (8 . "MASONRY") (62 . 7) (370 . 13) (100 . "AcDbLine") (10 17130.4666515837
1594.9121493213 0.0) (11 16957.0135746606 1594.9121493213 0.0))
((0 . "LINE") (100 . "AcDbEntity") (8 . "MASONRY") (62 . 7) (370 . 13) (100 . "AcDbLine") (10 16998.4898642534
584.4654751131 0.0) (11 16972.0983710407 584.4654751131 0.0))
((0 . "LINE") (100 . "AcDbEntity") (8 . "MASONRY") (62 . 7) (370 . 13) (100 . "AcDbLine") (10 16972.0983710407
573.1532579186 0.0) (11 16972.0983710407 584.4654751131 0.0))
((0 . "LINE") (100 . "AcDbEntity") (8 . "MASONRY") (62 . 7) (370 . 13) (100 . "AcDbLine") (10 16977.751719457
2281.2973642534 0.0) (11 16977.751719457 2262.443438914 0.0))
((0 . "LINE") (100 . "AcDbEntity") (8 . "MASONRY") (62 . 7) (370 . 13) (100 . "AcDbLine") (10 17175.718280543
2726.2443438914 0.0) (11 16979.6380090498 2726.2443438914 0.0))
((0 . "LINE") (100 . "AcDbEntity") (8 . "MASONRY") (62 . 7) (370 . 13) (100 . "AcDbLine") (10 16981.5242986425
2190.1975565611 0.0) (11 17017.347239819 2190.1975565611 0.0))
((0 . "LINE") (100 . "AcDbEntity") (8 . "MASONRY") (62 . 7) (370 . 13) (100 . "AcDbLine") (10 16981.5242986425
2190.1975565611 0.0) (11 16981.5242986425 2205.8823529412 0.0))
((0 . "LINE") (100 . "AcDbEntity") (8 . "MASONRY") (62 . 7) (370 . 13) (100 . "AcDbLine") (10 16983.4105882353
2239.8190045249 0.0) (11 16983.4105882353 2224.7362782805 0.0))
((0 . "LINE") (100 . "AcDbEntity") (8 . "MASONRY") (62 . 7) (370 . 13) (100 . "AcDbLine") (10 16983.4105882353
1892.910780543 0.0) (11 16983.4105882353 1900.4524886878 0.0))
((0 . "LINE") (100 . "AcDbEntity") (8 . "MASONRY") (62 . 7) (370 . 13) (100 . "AcDbLine") (10 16983.4105882353
1858.9741289593 0.0) (11 16990.9502262443 1858.9741289593 0.0))
((0 . "LINE") (100 . "AcDbEntity") (8 . "MASONRY") (62 . 7) (370 . 13) (100 . "AcDbLine") (10 16994.7228054299
1674.2081447964 0.0) (11 16983.4105882353 1674.2081447964 0.0))
((0 . "LINE") (100 . "AcDbEntity") (8 . "MASONRY") (62 . 7) (370 . 13) (100 . "AcDbLine") (10 17183.257918552
1955.1286651584 0.0) (11 16987.1776470588 1955.1286651584 0.0))
((0 . "LINE") (100 . "AcDbEntity") (8 . "MASONRY") (62 . 7) (370 . 13) (100 . "AcDbLine") (10 16987.1776470588
1938.1596493213 0.0) (11 16987.1776470588 1955.1286651584 0.0))
((0 . "LINE") (100 . "AcDbEntity") (8 . "MASONRY") (62 . 7) (370 . 13) (100 . "AcDbLine") (10 17006.0350226244
3337.1040723982 0.0) (11 17006.0350226244 3256.1848529412 0.0))
((0 . "LINE") (100 . "AcDbEntity") (8 . "MASONRY") (62 . 7) (370 . 13) (100 . "AcDbLine") (10 17006.0350226244
3337.1040723982 0.0) (11 17183.257918552 3337.1040723982 0.0))
((0 . "LINE") (100 . "AcDbEntity") (8 . "MASONRY") (62 . 7) (370 . 13) (100 . "AcDbLine") (10 17006.0350226244
3256.1848529412 0.0) (11 17032.4265158371 3256.1848529412 0.0))
((0 . "LINE") (100 . "AcDbEntity") (8 . "MASONRY") (62 . 7) (370 . 13) (100 . "AcDbLine") (10 17032.4265158371
3256.1848529412 0.0) (11 17183.257918552 3256.1848529412 0.0))
((0 . "LINE") (100 . "AcDbEntity") (8 . "MASONRY") (62 . 7) (370 . 13) (100 . "AcDbLine") (10 17007.9185520362
2509.4273076923 0.0) (11 17007.9185520362 2488.6877828054 0.0))
((0 . "LINE") (100 . "AcDbEntity") (8 . "MASONRY") (62 . 7) (370 . 13) (100 . "AcDbLine") (10 17024.8868778281
2418.9295701357 0.0) (11 17011.6938914027 2418.9295701357 0.0))
((0 . "LINE") (100 . "AcDbEntity") (8 . "MASONRY") (62 . 7) (370 . 13) (100 . "AcDbLine") (10 17134.2364705882
2450.9032918552 0.0) (11 17011.6938914027 2450.9032918552 0.0))
((0 . "LINE") (100 . "AcDbEntity") (8 . "MASONRY") (62 . 7) (370 . 13) (100 . "AcDbLine") (10 17011.6938914027
2450.9032918552 0.0) (11 17011.6938914027 2418.9295701357 0.0))
((0 . "LINE") (100 . "AcDbEntity") (8 . "MASONRY") (62 . 7) (370 . 13) (100 . "AcDbLine") (10 17007.9185520362
2509.4273076923 0.0) (11 17175.718280543 2509.4273076923 0.0))
((0 . "LINE") (100 . "AcDbEntity") (8 . "MASONRY") (62 . 7) (370 . 13) (100 . "AcDbLine") (10 17009.802081448
1434.7666742081 0.0) (11 17009.802081448 1417.7969683258 0.0))
((0 . "LINE") (100 . "AcDbEntity") (8 . "MASONRY") (62 . 7) (370 . 13) (100 . "AcDbLine") (10 17009.802081448
1434.7666742081 0.0) (11 17130.4666515837 1434.7666742081 0.0))
((0 . "LINE") (100 . "AcDbEntity") (8 . "MASONRY") (62 . 7) (370 . 13) (100 . "AcDbLine") (10 17017.347239819
1380.0904977376 0.0) (11 17017.347239819 1365.0084615385 0.0))
((0 . "LINE") (100 . "AcDbEntity") (8 . "MASONRY") (62 . 7) (370 . 13) (100 . "AcDbLine") (10 17126.6968325792
727.751719457 0.0) (11 17011.6869909502 727.751719457 0.0))
((0 . "LINE") (100 . "AcDbEntity") (8 . "MASONRY") (62 . 7) (370 . 13) (100 . "AcDbLine") (10 17024.8868778281
554.2986425339 0.0) (11 17024.8868778281 524.1318099548 0.0))
((0 . "LINE") (100 . "AcDbEntity") (8 . "MASONRY") (62 . 7) (370 . 13) (100 . "AcDbLine") (10 17021.1142986425
3099.5475113122 0.0) (11 17081.4479638009 3099.5475113122 0.0))
((0 . "LINE") (100 . "AcDbEntity") (8 . "MASONRY") (62 . 7) (370 . 13) (100 . "AcDbLine") (10 17021.1142986425
822.0220361991 0.0) (11 17179.4853393665 822.0220361991 0.0))
((0 . "LINE") (100 . "AcDbEntity") (8 . "MASONRY") (62 . 7) (370 . 13) (100 . "AcDbLine") (10 17028.6594570136
3050.5281334842 0.0) (11 17028.6594570136 3069.3813687783 0.0))
((0 . "LINE") (100 . "AcDbEntity") (8 . "MASONRY") (62 . 7) (370 . 13) (100 . "AcDbLine") (10 17028.6594570136
3050.5281334842 0.0) (11 17179.4853393665 3050.5281334842 0.0))
((0 . "LINE") (100 . "AcDbEntity") (8 . "MASONRY") (62 . 7) (370 . 13) (100 . "AcDbLine") (10 17062.5961085973
586.3503846154 0.0) (11 17036.1990950226 586.3503846154 0.0))
((0 . "LINE") (100 . "AcDbEntity") (8 . "MASONRY") (62 . 7) (370 . 13) (100 . "AcDbLine") (10 17043.7387330317
2417.0439705882 0.0) (11 17092.7601809955 2417.0439705882 0.0))
((0 . "LINE") (100 . "AcDbEntity") (8 . "MASONRY") (62 . 7) (370 . 13) (100 . "AcDbLine") (10 17153.0938461538
1078.4318325792 0.0) (11 17075.7918552036 1078.4318325792 0.0))
((0 . "LINE") (100 . "AcDbEntity") (8 . "MASONRY") (62 . 7) (370 . 13) (100 . "AcDbLine") (10 17075.7918552036
1104.8274660633 0.0) (11 17075.7918552036 1078.4318325792 0.0))
((0 . "LINE") (100 . "AcDbEntity") (8 . "MASONRY") (62 . 7) (370 . 13) (100 . "AcDbLine") (10 17092.7601809955
2631.9760972851 0.0) (11 17077.6753846154 2631.9760972851 0.0))
((0 . "LINE") (100 . "AcDbEntity") (8 . "MASONRY") (62 . 7) (370 . 13) (100 . "AcDbLine") (10 17077.6753846154
1823.1518778281 0.0) (11 17175.718280543 1823.1518778281 0.0))
((0 . "LINE") (100 . "AcDbEntity") (8 . "MASONRY") (62 . 7) (370 . 13) (100 . "AcDbLine") (10 17077.6753846154
531.6742081448 0.0) (11 17175.718280543 531.6742081448 0.0))
((0 . "LINE") (100 . "AcDbEntity") (8 . "MASONRY") (62 . 7) (370 . 13) (100 . "AcDbLine") (10 17179.4853393665
2009.8041515837 0.0) (11 17081.4479638009 2009.8041515837 0.0))
((0 . "LINE") (100 . "AcDbEntity") (8 . "MASONRY") (62 . 7) (370 . 13) (100 . "AcDbLine") (10 17179.4853393665
584.4654751131 0.0) (11 17107.8449773756 584.4654751131 0.0))
((0 . "LINE") (100 . "AcDbEntity") (8 . "MASONRY") (62 . 7) (370 . 13) (100 . "AcDbLine") (10 17130.4694117647
3099.5475113122 0.0) (11 17111.6120361991 3099.5475113122 0.0))
((0 . "LINE") (100 . "AcDbEntity") (8 . "MASONRY") (62 . 7) (370 . 13) (100 . "AcDbLine") (10 17134.2364705882
2417.0439705882 0.0) (11 17122.9242533937 2417.0439705882 0.0))
((0 . "LINE") (100 . "AcDbEntity") (8 . "MASONRY") (62 . 7) (370 . 13) (100 . "AcDbLine") (10 17130.4666515837
1594.9121493213 0.0) (11 17130.4666515837 1493.2126696833 0.0))
((0 . "LINE") (100 . "AcDbEntity") (8 . "MASONRY") (62 . 7) (370 . 13) (100 . "AcDbLine") (10 17130.4666515837
1493.2126696833 0.0) (11 17130.4666515837 1478.1292533937 0.0))
((0 . "LINE") (100 . "AcDbEntity") (8 . "MASONRY") (62 . 7) (370 . 13) (100 . "AcDbLine") (10 17179.4853393665
1594.9121493213 0.0) (11 17130.4666515837 1594.9121493213 0.0))
((0 . "LINE") (100 . "AcDbEntity") (8 . "MASONRY") (62 . 7) (370 . 13) (100 . "AcDbLine") (10 17126.6968325792
2631.9760972851 0.0) (11 17179.4853393665 2631.9760972851 0.0))
((0 . "LINE") (100 . "AcDbEntity") (8 . "MASONRY") (62 . 7) (370 . 13) (100 . "AcDbLine") (10 17130.4694117647
3182.799739819 0.0) (11 17130.4694117647 3152.3380882353 0.0))
((0 . "LINE") (100 . "AcDbEntity") (8 . "MASONRY") (62 . 7) (370 . 13) (100 . "AcDbLine") (10 17130.4694117647
3182.799739819 0.0) (11 17183.257918552 3182.799739819 0.0))
((0 . "LINE") (100 . "AcDbEntity") (8 . "MASONRY") (62 . 7) (370 . 13) (100 . "AcDbLine") (10 17130.4694117647
3129.7136538462 0.0) (11 17130.4694117647 3099.5475113122 0.0))
((0 . "LINE") (100 . "AcDbEntity") (8 . "MASONRY") (62 . 7) (370 . 13) (100 . "AcDbLine") (10 17145.5486877828
3099.5475113122 0.0) (11 17130.4694117647 3099.5475113122 0.0))
((0 . "LINE") (100 . "AcDbEntity") (8 . "MASONRY") (62 . 7) (370 . 13) (100 . "AcDbLine") (10 17179.4853393665
2611.2372624434 0.0) (11 17134.2364705882 2611.2372624434 0.0))
((0 . "LINE") (100 . "AcDbEntity") (8 . "MASONRY") (62 . 7) (370 . 13) (100 . "AcDbLine") (10 17134.2364705882
2417.0439705882 0.0) (11 17134.2364705882 2450.9032918552 0.0))
((0 . "LINE") (100 . "AcDbEntity") (8 . "MASONRY") (62 . 7) (370 . 13) (100 . "AcDbLine") (10 17134.2364705882
2488.6877828054 0.0) (11 17134.2364705882 2450.9032918552 0.0))
((0 . "LINE") (100 . "AcDbEntity") (8 . "MASONRY") (62 . 7) (370 . 13) (100 . "AcDbLine") (10 17153.0938461538
2417.0439705882 0.0) (11 17134.2364705882 2417.0439705882 0.0))
((0 . "LINE") (100 . "AcDbEntity") (8 . "MASONRY") (62 . 7) (370 . 13) (100 . "AcDbLine") (10 17130.4666515837
1434.7666742081 0.0) (11 17130.4666515837 1478.1292533937 0.0))
((0 . "LINE") (100 . "AcDbEntity") (8 . "MASONRY") (62 . 7) (370 . 13) (100 . "AcDbLine") (10 17153.0938461538
1478.1292533937 0.0) (11 17130.4666515837 1478.1292533937 0.0))
((0 . "LINE") (100 . "AcDbEntity") (8 . "MASONRY") (62 . 7) (370 . 13) (100 . "AcDbLine") (10 17175.718280543
1434.7666742081 0.0) (11 17130.4666515837 1434.7666742081 0.0))
((0 . "LINE") (100 . "AcDbEntity") (8 . "MASONRY") (62 . 7) (370 . 13) (100 . "AcDbLine") (10 17162.5197737557
3469.0801696833 0.0) (11 17179.4853393665 3469.0801696833 0.0))
((0 . "LINE") (100 . "AcDbEntity") (8 . "MASONRY") (62 . 7) (370 . 13) (100 . "AcDbLine") (10 17162.5197737557
3469.0801696833 0.0) (11 17162.5197737557 3487.9334049774 0.0))
((0 . "LINE") (100 . "AcDbEntity") (8 . "MASONRY") (62 . 7) (370 . 13) (100 . "AcDbLine") (10 17175.718280543
729.6380090498 0.0) (11 17168.1731221719 729.6380090498 0.0))
((0 . "LINE") (100 . "AcDbEntity") (8 . "MASONRY") (62 . 7) (370 . 13) (100 . "AcDbLine") (10 17183.257918552
2816.742081448 0.0) (11 17175.718280543 2816.742081448 0.0))
((0 . "LINE") (100 . "AcDbEntity") (8 . "MASONRY") (62 . 7) (370 . 13) (100 . "AcDbLine") (10 17228.5067873303
1087.319219457 0.0) (11 17209.6549321267 1087.319219457 0.0))
((0 . "LINE") (100 . "AcDbEntity") (8 . "MASONRY") (62 . 7) (370 . 13) (100 . "AcDbLine") (10 4321.2669683258
1227.6732579186 0.0) (11 4321.2669683258 1163.2734615385 0.0))
((0 . "LINE") (100 . "AcDbEntity") (8 . "MASONRY") (62 . 7) (370 . 13) (100 . "AcDbLine") (10 4210.0309615385
1163.2734615385 0.0) (11 4321.2669683258 1163.2734615385 0.0))
((0 . "LINE") (100 . "AcDbEntity") (8 . "MASONRY") (62 . 7) (370 . 13) (100 . "AcDbLine") (10 4321.2669683258
1163.2734615385 0.0) (11 4332.5791855204 1163.2734615385 0.0))
((0 . "LINE") (100 . "AcDbEntity") (8 . "MASONRY") (62 . 7) (370 . 13) (100 . "AcDbLine") (10 4160.633178733
1099.0940271493 0.0) (11 4321.2669683258 1099.0940271493 0.0))
((0 . "LINE") (100 . "AcDbEntity") (8 . "MASONRY") (62 . 7) (370 . 13) (100 . "AcDbLine") (10 4321.2669683258
1099.0940271493 0.0) (11 4332.5791855204 1099.0940271493 0.0))
((0 . "LINE") (100 . "AcDbEntity") (8 . "MASONRY") (62 . 7) (370 . 13) (100 . "AcDbLine") (10 6561.0859728507
1099.0940271493 0.0) (11 6620.306300905 1099.0940271493 0.0))
((0 . "LINE") (100 . "AcDbEntity") (8 . "MASONRY") (62 . 7) (370 . 13) (100 . "AcDbLine") (10 4321.2669683258
1099.0940271493 0.0) (11 4321.2669683258 991.7039140271 0.0))
((0 . "LINE") (100 . "AcDbEntity") (8 . "MASONRY") (62 . 7) (370 . 13) (100 . "AcDbLine") (10 6628.9592760181
1089.2049095023 0.0) (11 6628.9592760181 991.7039140271 0.0))
((0 . "LINE") (100 . "AcDbEntity") (8 . "MASONRY") (62 . 7) (370 . 13) (100 . "AcDbLine") (10 4127.0737669683
991.7039140271 0.0) (11 4128.9592760181 991.7039140271 0.0))
((0 . "LINE") (100 . "AcDbEntity") (8 . "MASONRY") (62 . 7) (370 . 13) (100 . "AcDbLine") (10 4128.9592760181
991.7039140271 0.0) (11 4321.2669683258 991.7039140271 0.0))
((0 . "LINE") (100 . "AcDbEntity") (8 . "MASONRY") (62 . 7) (370 . 13) (100 . "AcDbLine") (10 4321.2669683258
991.7039140271 0.0) (11 4332.5791855204 991.7039140271 0.0))
((0 . "LINE") (100 . "AcDbEntity") (8 . "MASONRY") (62 . 7) (370 . 13) (100 . "AcDbLine") (10 6561.0859728507
991.7039140271 0.0) (11 6628.9592760181 991.7039140271 0.0))
((0 . "LINE") (100 . "AcDbEntity") (8 . "MASONRY") (62 . 7) (370 . 13) (100 . "AcDbLine") (10 6628.9592760181
991.7039140271 0.0) (11 6714.2726470588 991.7039140271 0.0))
((0 . "LINE") (100 . "AcDbEntity") (8 . "MASONRY") (62 . 7) (370 . 13) (100 . "AcDbLine") (10 4128.9592760181
991.7039140271 0.0) (11 4128.9592760181 961.5384615385 0.0))
((0 . "LINE") (100 . "AcDbEntity") (8 . "MASONRY") (62 . 7) (370 . 13) (100 . "AcDbLine") (10 2993.3004411765
805.1117081448 0.0) (11 3048.3675791855 805.1117081448 0.0))
((0 . "LINE") (100 . "AcDbEntity") (8 . "MASONRY") (62 . 7) (370 . 13) (100 . "AcDbLine") (10 3234.1410067873
805.1117081448 0.0) (11 3295.7986312217 805.1117081448 0.0))
((0 . "LINE") (100 . "AcDbEntity") (8 . "MASONRY") (62 . 7) (370 . 13) (100 . "AcDbLine") (10 7072.2994570136
805.1117081448 0.0) (11 7151.7492986425 805.1117081448 0.0))
((0 . "LINE") (100 . "AcDbEntity") (8 . "MASONRY") (62 . 7) (370 . 13) (100 . "AcDbLine") (10 7320.5448076923
805.1117081448 0.0) (11 7382.4997850679 805.1117081448 0.0))
((0 . "LINE") (100 . "AcDbEntity") (8 . "MASONRY") (62 . 7) (370 . 13) (100 . "AcDbLine") (10 7604.6295927602
805.1117081448 0.0) (11 7624.4343891403 805.1117081448 0.0))
((0 . "LINE") (100 . "AcDbEntity") (8 . "MASONRY") (62 . 7) (370 . 13) (100 . "AcDbLine") (10 3552.036199095
799.6323529412 0.0) (11 3552.036199095 735.2941176471 0.0))
((0 . "LINE") (100 . "AcDbEntity") (8 . "MASONRY") (62 . 7) (370 . 13) (100 . "AcDbLine") (10 7398.1900452489
771.1161425339 0.0) (11 7398.1900452489 727.751719457 0.0))
((0 . "LINE") (100 . "AcDbEntity") (8 . "MASONRY") (62 . 7) (370 . 13) (100 . "AcDbLine") (10 3014.6411199095
727.751719457 0.0) (11 3134.3231221719 727.751719457 0.0))
((0 . "LINE") (100 . "AcDbEntity") (8 . "MASONRY") (62 . 7) (370 . 13) (100 . "AcDbLine") (10 3215.7219683258
727.751719457 0.0) (11 3325.142081448 727.751719457 0.0))
((0 . "LINE") (100 . "AcDbEntity") (8 . "MASONRY") (62 . 7) (370 . 13) (100 . "AcDbLine") (10 3497.27 727.751719457 0.0)
(11 3550.9587104072 727.751719457 0.0))
((0 . "LINE") (100 . "AcDbEntity") (8 . "MASONRY") (62 . 7) (370 . 13) (100 . "AcDbLine") (10 7048.2911764706
727.751719457 0.0) (11 7179.4874095023 727.751719457 0.0))
((0 . "LINE") (100 . "AcDbEntity") (8 . "MASONRY") (62 . 7) (370 . 13) (100 . "AcDbLine") (10 7179.4874095023
727.751719457 0.0) (11 7205.8823529412 727.751719457 0.0))
((0 . "LINE") (100 . "AcDbEntity") (8 . "MASONRY") (62 . 7) (370 . 13) (100 . "AcDbLine") (10 7205.8823529412
727.751719457 0.0) (11 7220.9661312217 727.751719457 0.0))
((0 . "LINE") (100 . "AcDbEntity") (8 . "MASONRY") (62 . 7) (370 . 13) (100 . "AcDbLine") (10 7302.1257579186
727.751719457 0.0) (11 7398.1900452489 727.751719457 0.0))
((0 . "LINE") (100 . "AcDbEntity") (8 . "MASONRY") (62 . 7) (370 . 13) (100 . "AcDbLine") (10 7398.1900452489
727.751719457 0.0) (11 7418.2043891403 727.751719457 0.0))
((0 . "LINE") (100 . "AcDbEntity") (8 . "MASONRY") (62 . 7) (370 . 13) (100 . "AcDbLine") (10 7556.7400791855
727.751719457 0.0) (11 7590.4977375566 727.751719457 0.0))
((0 . "LINE") (100 . "AcDbEntity") (8 . "MASONRY") (62 . 7) (370 . 13) (100 . "AcDbLine") (10 7590.4977375566
727.751719457 0.0) (11 7624.4343891403 727.751719457 0.0))
((0 . "LINE") (100 . "AcDbEntity") (8 . "MASONRY") (62 . 7) (370 . 13) (100 . "AcDbLine") (10 3359.7285067873
636.5693099548 0.0) (11 3359.7285067873 588.2415045249 0.0))
((0 . "LINE") (100 . "AcDbEntity") (8 . "MASONRY") (62 . 7) (370 . 13) (100 . "AcDbLine") (10 7205.8823529412
727.751719457 0.0) (11 7205.8823529412 588.2415045249 0.0))
((0 . "LINE") (100 . "AcDbEntity") (8 . "MASONRY") (62 . 7) (370 . 13) (100 . "AcDbLine") (10 7590.4977375566
727.751719457 0.0) (11 7590.4977375566 588.2415045249 0.0))
((0 . "LINE") (100 . "AcDbEntity") (8 . "MASONRY") (62 . 7) (370 . 13) (100 . "AcDbLine") (10 3053.1266968326
588.2415045249 0.0) (11 3167.4208144796 588.2415045249 0.0))
((0 . "LINE") (100 . "AcDbEntity") (8 . "MASONRY") (62 . 7) (370 . 13) (100 . "AcDbLine") (10 3167.4208144796
588.2415045249 0.0) (11 3359.7285067873 588.2415045249 0.0))
((0 . "LINE") (100 . "AcDbEntity") (8 . "MASONRY") (62 . 7) (370 . 13) (100 . "AcDbLine") (10 3359.7285067873
588.2415045249 0.0) (11 3378.059739819 588.2415045249 0.0))
((0 . "LINE") (100 . "AcDbEntity") (8 . "MASONRY") (62 . 7) (370 . 13) (100 . "AcDbLine") (10 3390.9765045249
588.2415045249 0.0) (11 3531.0286877828 588.2415045249 0.0))
((0 . "LINE") (100 . "AcDbEntity") (8 . "MASONRY") (62 . 7) (370 . 13) (100 . "AcDbLine") (10 3965.5695588235
588.2415045249 0.0) (11 3996.9751244344 588.2415045249 0.0))
((0 . "LINE") (100 . "AcDbEntity") (8 . "MASONRY") (62 . 7) (370 . 13) (100 . "AcDbLine") (10 7004.9949095023
588.2415045249 0.0) (11 7013.5746606335 588.2415045249 0.0))
((0 . "LINE") (100 . "AcDbEntity") (8 . "MASONRY") (62 . 7) (370 . 13) (100 . "AcDbLine") (10 7013.5746606335
588.2415045249 0.0) (11 7205.8823529412 588.2415045249 0.0))
((0 . "LINE") (100 . "AcDbEntity") (8 . "MASONRY") (62 . 7) (370 . 13) (100 . "AcDbLine") (10 7205.8823529412
588.2415045249 0.0) (11 7398.1900452489 588.2415045249 0.0))
((0 . "LINE") (100 . "AcDbEntity") (8 . "MASONRY") (62 . 7) (370 . 13) (100 . "AcDbLine") (10 7398.1900452489
588.2415045249 0.0) (11 7590.4977375566 588.2415045249 0.0))
((0 . "LINE") (100 . "AcDbEntity") (8 . "MASONRY") (62 . 7) (370 . 13) (100 . "AcDbLine") (10 7590.4977375566
588.2415045249 0.0) (11 7624.4343891403 588.2415045249 0.0))
((0 . "LINE") (100 . "AcDbEntity") (8 . "MASONRY") (62 . 7) (370 . 13) (100 . "AcDbLine") (10 3167.4208144796
588.2415045249 0.0) (11 3167.4208144796 514.7114027149 0.0))
((0 . "LINE") (100 . "AcDbEntity") (8 . "MASONRY") (62 . 7) (370 . 13) (100 . "AcDbLine") (10 3936.6515837104
568.2213687783 0.0) (11 3936.6515837104 514.7114027149 0.0))
((0 . "LINE") (100 . "AcDbEntity") (8 . "MASONRY") (62 . 7) (370 . 13) (100 . "AcDbLine") (10 4321.2669683258
542.9864253394 0.0) (11 4321.2669683258 514.7114027149 0.0))
((0 . "LINE") (100 . "AcDbEntity") (8 . "MASONRY") (62 . 7) (370 . 13) (100 . "AcDbLine") (10 5475.1131221719
541.7295135747 0.0) (11 5475.1131221719 514.7114027149 0.0))
((0 . "LINE") (100 . "AcDbEntity") (8 . "MASONRY") (62 . 7) (370 . 13) (100 . "AcDbLine") (10 7013.5746606335
588.2415045249 0.0) (11 7013.5746606335 514.7114027149 0.0))
((0 . "LINE") (100 . "AcDbEntity") (8 . "MASONRY") (62 . 7) (370 . 13) (100 . "AcDbLine") (10 7398.1900452489
588.2415045249 0.0) (11 7398.1900452489 514.7114027149 0.0))
((0 . "LINE") (100 . "AcDbEntity") (8 . "MASONRY") (62 . 7) (370 . 13) (100 . "AcDbLine") (10 2827.1849773756
514.7114027149 0.0) (11 2975.1131221719 514.7114027149 0.0))
((0 . "LINE") (100 . "AcDbEntity") (8 . "MASONRY") (62 . 7) (370 . 13) (100 . "AcDbLine") (10 2975.1131221719
514.7114027149 0.0) (11 3167.4208144796 514.7114027149 0.0))
((0 . "LINE") (100 . "AcDbEntity") (8 . "MASONRY") (62 . 7) (370 . 13) (100 . "AcDbLine") (10 3167.4208144796
514.7114027149 0.0) (11 3359.7285067873 514.7114027149 0.0))
((0 . "LINE") (100 . "AcDbEntity") (8 . "MASONRY") (62 . 7) (370 . 13) (100 . "AcDbLine") (10 3359.7285067873
514.7114027149 0.0) (11 3520.5243778281 514.7114027149 0.0))
((0 . "LINE") (100 . "AcDbEntity") (8 . "MASONRY") (62 . 7) (370 . 13) (100 . "AcDbLine") (10 3859.3594117647
514.7114027149 0.0) (11 3936.6515837104 514.7114027149 0.0))
((0 . "LINE") (100 . "AcDbEntity") (8 . "MASONRY") (62 . 7) (370 . 13) (100 . "AcDbLine") (10 3936.6515837104
514.7114027149 0.0) (11 4095.015260181 514.7114027149 0.0))
((0 . "LINE") (100 . "AcDbEntity") (8 . "MASONRY") (62 . 7) (370 . 13) (100 . "AcDbLine") (10 4264.7169343891
514.7114027149 0.0) (11 4321.2669683258 514.7114027149 0.0))
((0 . "LINE") (100 . "AcDbEntity") (8 . "MASONRY") (62 . 7) (370 . 13) (100 . "AcDbLine") (10 4321.2669683258
514.7114027149 0.0) (11 4488.6745248869 514.7114027149 0.0))
((0 . "LINE") (100 . "AcDbEntity") (8 . "MASONRY") (62 . 7) (370 . 13) (100 . "AcDbLine") (10 4781.121300905
514.7114027149 0.0) (11 4898.1900452489 514.7114027149 0.0))
((0 . "LINE") (100 . "AcDbEntity") (8 . "MASONRY") (62 . 7) (370 . 13) (100 . "AcDbLine") (10 4898.1900452489
514.7114027149 0.0) (11 5032.3795135747 514.7114027149 0.0))
((0 . "LINE") (100 . "AcDbEntity") (8 . "MASONRY") (62 . 7) (370 . 13) (100 . "AcDbLine") (10 5365.9607239819
514.7114027149 0.0) (11 5475.1131221719 514.7114027149 0.0))
((0 . "LINE") (100 . "AcDbEntity") (8 . "MASONRY") (62 . 7) (370 . 13) (100 . "AcDbLine") (10 5475.1131221719
514.7114027149 0.0) (11 5548.0620135747 514.7114027149 0.0))
((0 . "LINE") (100 . "AcDbEntity") (8 . "MASONRY") (62 . 7) (370 . 13) (100 . "AcDbLine") (10 5881.4203846154
514.7114027149 0.0) (11 6052.036199095 514.7114027149 0.0))
((0 . "LINE") (100 . "AcDbEntity") (8 . "MASONRY") (62 . 7) (370 . 13) (100 . "AcDbLine") (10 6052.036199095
514.7114027149 0.0) (11 6147.5480882353 514.7114027149 0.0))
((0 . "LINE") (100 . "AcDbEntity") (8 . "MASONRY") (62 . 7) (370 . 13) (100 . "AcDbLine") (10 6368.0885294118
514.7114027149 0.0) (11 6436.6515837104 514.7114027149 0.0))
((0 . "LINE") (100 . "AcDbEntity") (8 . "MASONRY") (62 . 7) (370 . 13) (100 . "AcDbLine") (10 6436.6515837104
514.7114027149 0.0) (11 6651.5702036199 514.7114027149 0.0))
((0 . "LINE") (100 . "AcDbEntity") (8 . "MASONRY") (62 . 7) (370 . 13) (100 . "AcDbLine") (10 6914.2037443439
514.7114027149 0.0) (11 7013.5746606335 514.7114027149 0.0))
((0 . "LINE") (100 . "AcDbEntity") (8 . "MASONRY") (62 . 7) (370 . 13) (100 . "AcDbLine") (10 7013.5746606335
514.7114027149 0.0) (11 7205.8823529412 514.7114027149 0.0))
((0 . "LINE") (100 . "AcDbEntity") (8 . "MASONRY") (62 . 7) (370 . 13) (100 . "AcDbLine") (10 7205.8823529412
514.7114027149 0.0) (11 7398.1900452489 514.7114027149 0.0))
((0 . "LINE") (100 . "AcDbEntity") (8 . "MASONRY") (62 . 7) (370 . 13) (100 . "AcDbLine") (10 7398.1900452489
514.7114027149 0.0) (11 7590.4977375566 514.7114027149 0.0))
((0 . "LINE") (100 . "AcDbEntity") (8 . "MASONRY") (62 . 7) (370 . 13) (100 . "AcDbLine") (10 7590.4977375566
514.7114027149 0.0) (11 7624.4343891403 514.7114027149 0.0))
((0 . "LINE") (100 . "AcDbEntity") (8 . "MASONRY") (62 . 7) (370 . 13) (100 . "AcDbLine") (10 2975.1131221719
514.7114027149 0.0) (11 2975.1131221719 441.181300905 0.0))
((0 . "LINE") (100 . "AcDbEntity") (8 . "MASONRY") (62 . 7) (370 . 13) (100 . "AcDbLine") (10 3359.7285067873
514.7114027149 0.0) (11 3359.7285067873 441.181300905 0.0))
((0 . "LINE") (100 . "AcDbEntity") (8 . "MASONRY") (62 . 7) (370 . 13) (100 . "AcDbLine") (10 3744.3438914027
497.7375565611 0.0) (11 3744.3438914027 441.181300905 0.0))
((0 . "LINE") (100 . "AcDbEntity") (8 . "MASONRY") (62 . 7) (370 . 13) (100 . "AcDbLine") (10 4128.9592760181
489.2533936652 0.0) (11 4128.9592760181 441.181300905 0.0))
((0 . "LINE") (100 . "AcDbEntity") (8 . "MASONRY") (62 . 7) (370 . 13) (100 . "AcDbLine") (10 4513.5746606335
504.3363461538 0.0) (11 4513.5746606335 441.181300905 0.0))
((0 . "LINE") (100 . "AcDbEntity") (8 . "MASONRY") (62 . 7) (370 . 13) (100 . "AcDbLine") (10 4898.1900452489
514.7114027149 0.0) (11 4898.1900452489 441.181300905 0.0))
((0 . "LINE") (100 . "AcDbEntity") (8 . "MASONRY") (62 . 7) (370 . 13) (100 . "AcDbLine") (10 5282.8054298643
470.9454638009 0.0) (11 5282.8054298643 441.181300905 0.0))
((0 . "LINE") (100 . "AcDbEntity") (8 . "MASONRY") (62 . 7) (370 . 13) (100 . "AcDbLine") (10 5667.4208144796
470.5044457014 0.0) (11 5667.4208144796 441.181300905 0.0))
((0 . "LINE") (100 . "AcDbEntity") (8 . "MASONRY") (62 . 7) (370 . 13) (100 . "AcDbLine") (10 6052.036199095
514.7114027149 0.0) (11 6052.036199095 441.181300905 0.0))
((0 . "LINE") (100 . "AcDbEntity") (8 . "MASONRY") (62 . 7) (370 . 13) (100 . "AcDbLine") (10 6436.6515837104
514.7114027149 0.0) (11 6436.6515837104 441.181300905 0.0))
((0 . "LINE") (100 . "AcDbEntity") (8 . "MASONRY") (62 . 7) (370 . 13) (100 . "AcDbLine") (10 6821.2669683258
480.4715384615 0.0) (11 6821.2669683258 441.181300905 0.0))
((0 . "LINE") (100 . "AcDbEntity") (8 . "MASONRY") (62 . 7) (370 . 13) (100 . "AcDbLine") (10 7205.8823529412
514.7114027149 0.0) (11 7205.8823529412 441.181300905 0.0))
((0 . "LINE") (100 . "AcDbEntity") (8 . "MASONRY") (62 . 7) (370 . 13) (100 . "AcDbLine") (10 7590.4977375566
514.7114027149 0.0) (11 7590.4977375566 441.181300905 0.0))
((0 . "LINE") (100 . "AcDbEntity") (8 . "MASONRY") (62 . 7) (370 . 13) (100 . "AcDbLine") (10 2815.872658371
441.181300905 0.0) (11 2975.1131221719 441.181300905 0.0))
((0 . "LINE") (100 . "AcDbEntity") (8 . "MASONRY") (62 . 7) (370 . 13) (100 . "AcDbLine") (10 2975.1131221719
441.181300905 0.0) (11 3167.4208144796 441.181300905 0.0))
((0 . "LINE") (100 . "AcDbEntity") (8 . "MASONRY") (62 . 7) (370 . 13) (100 . "AcDbLine") (10 3167.4208144796
441.181300905 0.0) (11 3359.7285067873 441.181300905 0.0))
((0 . "LINE") (100 . "AcDbEntity") (8 . "MASONRY") (62 . 7) (370 . 13) (100 . "AcDbLine") (10 3359.7285067873
441.181300905 0.0) (11 3552.036199095 441.181300905 0.0))
((0 . "LINE") (100 . "AcDbEntity") (8 . "MASONRY") (62 . 7) (370 . 13) (100 . "AcDbLine") (10 3552.036199095
441.181300905 0.0) (11 3744.3438914027 441.181300905 0.0))
((0 . "LINE") (100 . "AcDbEntity") (8 . "MASONRY") (62 . 7) (370 . 13) (100 . "AcDbLine") (10 3744.3438914027
441.181300905 0.0) (11 3936.6515837104 441.181300905 0.0))
((0 . "LINE") (100 . "AcDbEntity") (8 . "MASONRY") (62 . 7) (370 . 13) (100 . "AcDbLine") (10 3936.6515837104
441.181300905 0.0) (11 4128.9592760181 441.181300905 0.0))
((0 . "LINE") (100 . "AcDbEntity") (8 . "MASONRY") (62 . 7) (370 . 13) (100 . "AcDbLine") (10 4128.9592760181
441.181300905 0.0) (11 4321.2669683258 441.181300905 0.0))
((0 . "LINE") (100 . "AcDbEntity") (8 . "MASONRY") (62 . 7) (370 . 13) (100 . "AcDbLine") (10 4321.2669683258
441.181300905 0.0) (11 4513.5746606335 441.181300905 0.0))
((0 . "LINE") (100 . "AcDbEntity") (8 . "MASONRY") (62 . 7) (370 . 13) (100 . "AcDbLine") (10 4513.5746606335
441.181300905 0.0) (11 4705.8823529412 441.181300905 0.0))
((0 . "LINE") (100 . "AcDbEntity") (8 . "MASONRY") (62 . 7) (370 . 13) (100 . "AcDbLine") (10 4705.8823529412
441.181300905 0.0) (11 4898.1900452489 441.181300905 0.0))
((0 . "LINE") (100 . "AcDbEntity") (8 . "MASONRY") (62 . 7) (370 . 13) (100 . "AcDbLine") (10 4898.1900452489
441.181300905 0.0) (11 5090.4977375566 441.181300905 0.0))
((0 . "LINE") (100 . "AcDbEntity") (8 . "MASONRY") (62 . 7) (370 . 13) (100 . "AcDbLine") (10 5090.4977375566
441.181300905 0.0) (11 5226.2316063348 441.181300905 0.0))
((0 . "LINE") (100 . "AcDbEntity") (8 . "MASONRY") (62 . 7) (370 . 13) (100 . "AcDbLine") (10 5226.2535294118
441.181300905 0.0) (11 5282.8054298643 441.181300905 0.0))
((0 . "LINE") (100 . "AcDbEntity") (8 . "MASONRY") (62 . 7) (370 . 13) (100 . "AcDbLine") (10 5282.8054298643
441.181300905 0.0) (11 5475.1131221719 441.181300905 0.0))
((0 . "LINE") (100 . "AcDbEntity") (8 . "MASONRY") (62 . 7) (370 . 13) (100 . "AcDbLine") (10 5475.1131221719
441.181300905 0.0) (11 5667.4208144796 441.181300905 0.0))
((0 . "LINE") (100 . "AcDbEntity") (8 . "MASONRY") (62 . 7) (370 . 13) (100 . "AcDbLine") (10 5667.4208144796
441.181300905 0.0) (11 5746.593280543 441.181300905 0.0))
((0 . "LINE") (100 . "AcDbEntity") (8 . "MASONRY") (62 . 7) (370 . 13) (100 . "AcDbLine") (10 5746.6151923077
441.181300905 0.0) (11 5859.7285067873 441.181300905 0.0))
((0 . "LINE") (100 . "AcDbEntity") (8 . "MASONRY") (62 . 7) (370 . 13) (100 . "AcDbLine") (10 5859.7285067873
441.181300905 0.0) (11 6052.036199095 441.181300905 0.0))
((0 . "LINE") (100 . "AcDbEntity") (8 . "MASONRY") (62 . 7) (370 . 13) (100 . "AcDbLine") (10 6052.036199095
441.181300905 0.0) (11 6244.3438914027 441.181300905 0.0))
((0 . "LINE") (100 . "AcDbEntity") (8 . "MASONRY") (62 . 7) (370 . 13) (100 . "AcDbLine") (10 6244.3438914027
441.181300905 0.0) (11 6436.6515837104 441.181300905 0.0))
((0 . "LINE") (100 . "AcDbEntity") (8 . "MASONRY") (62 . 7) (370 . 13) (100 . "AcDbLine") (10 6436.6515837104
441.181300905 0.0) (11 6628.9592760181 441.181300905 0.0))
((0 . "LINE") (100 . "AcDbEntity") (8 . "MASONRY") (62 . 7) (370 . 13) (100 . "AcDbLine") (10 6628.9592760181
441.181300905 0.0) (11 6821.2669683258 441.181300905 0.0))
((0 . "LINE") (100 . "AcDbEntity") (8 . "MASONRY") (62 . 7) (370 . 13) (100 . "AcDbLine") (10 6821.2669683258
441.181300905 0.0) (11 7013.5746606335 441.181300905 0.0))
((0 . "LINE") (100 . "AcDbEntity") (8 . "MASONRY") (62 . 7) (370 . 13) (100 . "AcDbLine") (10 7013.5746606335
441.181300905 0.0) (11 7205.8823529412 441.181300905 0.0))
((0 . "LINE") (100 . "AcDbEntity") (8 . "MASONRY") (62 . 7) (370 . 13) (100 . "AcDbLine") (10 7205.8823529412
441.181300905 0.0) (11 7398.1900452489 441.181300905 0.0))
((0 . "LINE") (100 . "AcDbEntity") (8 . "MASONRY") (62 . 7) (370 . 13) (100 . "AcDbLine") (10 7398.1900452489
441.181300905 0.0) (11 7590.4977375566 441.181300905 0.0))
((0 . "LINE") (100 . "AcDbEntity") (8 . "MASONRY") (62 . 7) (370 . 13) (100 . "AcDbLine") (10 7590.4977375566
441.181300905 0.0) (11 7782.8054298643 441.181300905 0.0))
((0 . "LINE") (100 . "AcDbEntity") (8 . "MASONRY") (62 . 7) (370 . 13) (100 . "AcDbLine") (10 7782.8054298643
441.181300905 0.0) (11 7835.5949660633 441.181300905 0.0))
((0 . "LINE") (100 . "AcDbEntity") (8 . "MASONRY") (62 . 7) (370 . 13) (100 . "AcDbLine") (10 3167.4208144796
441.181300905 0.0) (11 3167.4208144796 367.651199095 0.0))
((0 . "LINE") (100 . "AcDbEntity") (8 . "MASONRY") (62 . 7) (370 . 13) (100 . "AcDbLine") (10 3552.036199095
441.181300905 0.0) (11 3552.036199095 367.651199095 0.0))
((0 . "LINE") (100 . "AcDbEntity") (8 . "MASONRY") (62 . 7) (370 . 13) (100 . "AcDbLine") (10 3936.6515837104
441.181300905 0.0) (11 3936.6515837104 367.651199095 0.0))
((0 . "LINE") (100 . "AcDbEntity") (8 . "MASONRY") (62 . 7) (370 . 13) (100 . "AcDbLine") (10 4321.2669683258
441.181300905 0.0) (11 4321.2669683258 367.651199095 0.0))
((0 . "LINE") (100 . "AcDbEntity") (8 . "MASONRY") (62 . 7) (370 . 13) (100 . "AcDbLine") (10 4705.8823529412
441.181300905 0.0) (11 4705.8823529412 367.651199095 0.0))
((0 . "LINE") (100 . "AcDbEntity") (8 . "MASONRY") (62 . 7) (370 . 13) (100 . "AcDbLine") (10 5090.4977375566
441.181300905 0.0) (11 5090.4977375566 367.651199095 0.0))
((0 . "LINE") (100 . "AcDbEntity") (8 . "MASONRY") (62 . 7) (370 . 13) (100 . "AcDbLine") (10 5475.1131221719
441.181300905 0.0) (11 5475.1131221719 367.651199095 0.0))
((0 . "LINE") (100 . "AcDbEntity") (8 . "MASONRY") (62 . 7) (370 . 13) (100 . "AcDbLine") (10 5859.7285067873
441.181300905 0.0) (11 5859.7285067873 367.651199095 0.0))
((0 . "LINE") (100 . "AcDbEntity") (8 . "MASONRY") (62 . 7) (370 . 13) (100 . "AcDbLine") (10 6244.3438914027
441.181300905 0.0) (11 6244.3438914027 367.651199095 0.0))
((0 . "LINE") (100 . "AcDbEntity") (8 . "MASONRY") (62 . 7) (370 . 13) (100 . "AcDbLine") (10 6628.9592760181
441.181300905 0.0) (11 6628.9592760181 367.651199095 0.0))
((0 . "LINE") (100 . "AcDbEntity") (8 . "MASONRY") (62 . 7) (370 . 13) (100 . "AcDbLine") (10 7013.5746606335
441.181300905 0.0) (11 7013.5746606335 367.651199095 0.0))
((0 . "LINE") (100 . "AcDbEntity") (8 . "MASONRY") (62 . 7) (370 . 13) (100 . "AcDbLine") (10 7398.1900452489
441.181300905 0.0) (11 7398.1900452489 367.651199095 0.0))
((0 . "LINE") (100 . "AcDbEntity") (8 . "MASONRY") (62 . 7) (370 . 13) (100 . "AcDbLine") (10 7782.8054298643
441.181300905 0.0) (11 7782.8054298643 367.651199095 0.0))
((0 . "LINE") (100 . "AcDbEntity") (8 . "MASONRY") (62 . 7) (370 . 13) (100 . "AcDbLine") (10 2804.5603280543
367.651199095 0.0) (11 2975.1131221719 367.651199095 0.0))
((0 . "LINE") (100 . "AcDbEntity") (8 . "MASONRY") (62 . 7) (370 . 13) (100 . "AcDbLine") (10 2975.1131221719
367.651199095 0.0) (11 3167.4208144796 367.651199095 0.0))
((0 . "LINE") (100 . "AcDbEntity") (8 . "MASONRY") (62 . 7) (370 . 13) (100 . "AcDbLine") (10 3167.4208144796
367.651199095 0.0) (11 3359.7285067873 367.651199095 0.0))
((0 . "LINE") (100 . "AcDbEntity") (8 . "MASONRY") (62 . 7) (370 . 13) (100 . "AcDbLine") (10 3359.7285067873
367.651199095 0.0) (11 3552.036199095 367.651199095 0.0))
((0 . "LINE") (100 . "AcDbEntity") (8 . "MASONRY") (62 . 7) (370 . 13) (100 . "AcDbLine") (10 3552.036199095
367.651199095 0.0) (11 3744.3438914027 367.651199095 0.0))
((0 . "LINE") (100 . "AcDbEntity") (8 . "MASONRY") (62 . 7) (370 . 13) (100 . "AcDbLine") (10 3744.3438914027
367.651199095 0.0) (11 3936.6515837104 367.651199095 0.0))
((0 . "LINE") (100 . "AcDbEntity") (8 . "MASONRY") (62 . 7) (370 . 13) (100 . "AcDbLine") (10 3936.6515837104
367.651199095 0.0) (11 4128.9592760181 367.651199095 0.0))
((0 . "LINE") (100 . "AcDbEntity") (8 . "MASONRY") (62 . 7) (370 . 13) (100 . "AcDbLine") (10 4128.9592760181
367.651199095 0.0) (11 4321.2669683258 367.651199095 0.0))
((0 . "LINE") (100 . "AcDbEntity") (8 . "MASONRY") (62 . 7) (370 . 13) (100 . "AcDbLine") (10 4321.2669683258
367.651199095 0.0) (11 4513.5746606335 367.651199095 0.0))
((0 . "LINE") (100 . "AcDbEntity") (8 . "MASONRY") (62 . 7) (370 . 13) (100 . "AcDbLine") (10 4513.5746606335
367.651199095 0.0) (11 4705.8823529412 367.651199095 0.0))
((0 . "LINE") (100 . "AcDbEntity") (8 . "MASONRY") (62 . 7) (370 . 13) (100 . "AcDbLine") (10 4705.8823529412
367.651199095 0.0) (11 4898.1900452489 367.651199095 0.0))
((0 . "LINE") (100 . "AcDbEntity") (8 . "MASONRY") (62 . 7) (370 . 13) (100 . "AcDbLine") (10 4898.1900452489
367.651199095 0.0) (11 5090.4977375566 367.651199095 0.0))
((0 . "LINE") (100 . "AcDbEntity") (8 . "MASONRY") (62 . 7) (370 . 13) (100 . "AcDbLine") (10 5090.4977375566
367.651199095 0.0) (11 5282.8054298643 367.651199095 0.0))
((0 . "LINE") (100 . "AcDbEntity") (8 . "MASONRY") (62 . 7) (370 . 13) (100 . "AcDbLine") (10 5282.8054298643
367.651199095 0.0) (11 5475.1131221719 367.651199095 0.0))
((0 . "LINE") (100 . "AcDbEntity") (8 . "MASONRY") (62 . 7) (370 . 13) (100 . "AcDbLine") (10 5475.1131221719
367.651199095 0.0) (11 5667.4208144796 367.651199095 0.0))
((0 . "LINE") (100 . "AcDbEntity") (8 . "MASONRY") (62 . 7) (370 . 13) (100 . "AcDbLine") (10 5667.4208144796
367.651199095 0.0) (11 5859.7285067873 367.651199095 0.0))
((0 . "LINE") (100 . "AcDbEntity") (8 . "MASONRY") (62 . 7) (370 . 13) (100 . "AcDbLine") (10 5859.7285067873
367.651199095 0.0) (11 6052.036199095 367.651199095 0.0))
((0 . "LINE") (100 . "AcDbEntity") (8 . "MASONRY") (62 . 7) (370 . 13) (100 . "AcDbLine") (10 6052.036199095
367.651199095 0.0) (11 6244.3438914027 367.651199095 0.0))
((0 . "LINE") (100 . "AcDbEntity") (8 . "MASONRY") (62 . 7) (370 . 13) (100 . "AcDbLine") (10 6244.3438914027
367.651199095 0.0) (11 6436.6515837104 367.651199095 0.0))
((0 . "LINE") (100 . "AcDbEntity") (8 . "MASONRY") (62 . 7) (370 . 13) (100 . "AcDbLine") (10 6436.6515837104
367.651199095 0.0) (11 6628.9592760181 367.651199095 0.0))
((0 . "LINE") (100 . "AcDbEntity") (8 . "MASONRY") (62 . 7) (370 . 13) (100 . "AcDbLine") (10 6628.9592760181
367.651199095 0.0) (11 6821.2669683258 367.651199095 0.0))
((0 . "LINE") (100 . "AcDbEntity") (8 . "MASONRY") (62 . 7) (370 . 13) (100 . "AcDbLine") (10 6821.2669683258
367.651199095 0.0) (11 7013.5746606335 367.651199095 0.0))
((0 . "LINE") (100 . "AcDbEntity") (8 . "MASONRY") (62 . 7) (370 . 13) (100 . "AcDbLine") (10 7013.5746606335
367.651199095 0.0) (11 7205.8823529412 367.651199095 0.0))
((0 . "LINE") (100 . "AcDbEntity") (8 . "MASONRY") (62 . 7) (370 . 13) (100 . "AcDbLine") (10 7205.8823529412
367.651199095 0.0) (11 7398.1900452489 367.651199095 0.0))
((0 . "LINE") (100 . "AcDbEntity") (8 . "MASONRY") (62 . 7) (370 . 13) (100 . "AcDbLine") (10 7398.1900452489
367.651199095 0.0) (11 7590.4977375566 367.651199095 0.0))
((0 . "LINE") (100 . "AcDbEntity") (8 . "MASONRY") (62 . 7) (370 . 13) (100 . "AcDbLine") (10 7590.4977375566
367.651199095 0.0) (11 7782.8054298643 367.651199095 0.0))
((0 . "LINE") (100 . "AcDbEntity") (8 . "MASONRY") (62 . 7) (370 . 13) (100 . "AcDbLine") (10 7782.8054298643
367.651199095 0.0) (11 7847.8499886878 367.651199095 0.0))
((0 . "LINE") (100 . "AcDbEntity") (8 . "MASONRY") (62 . 7) (370 . 13) (100 . "AcDbLine") (10 2975.1131221719
367.651199095 0.0) (11 2975.1131221719 294.1210972851 0.0))
((0 . "LINE") (100 . "AcDbEntity") (8 . "MASONRY") (62 . 7) (370 . 13) (100 . "AcDbLine") (10 3359.7285067873
367.651199095 0.0) (11 3359.7285067873 294.1210972851 0.0))
((0 . "LINE") (100 . "AcDbEntity") (8 . "MASONRY") (62 . 7) (370 . 13) (100 . "AcDbLine") (10 3744.3438914027
367.651199095 0.0) (11 3744.3438914027 294.1210972851 0.0))
((0 . "LINE") (100 . "AcDbEntity") (8 . "MASONRY") (62 . 7) (370 . 13) (100 . "AcDbLine") (10 4128.9592760181
367.651199095 0.0) (11 4128.9592760181 294.1210972851 0.0))
((0 . "LINE") (100 . "AcDbEntity") (8 . "MASONRY") (62 . 7) (370 . 13) (100 . "AcDbLine") (10 4513.5746606335
367.651199095 0.0) (11 4513.5746606335 294.1210972851 0.0))
((0 . "LINE") (100 . "AcDbEntity") (8 . "MASONRY") (62 . 7) (370 . 13) (100 . "AcDbLine") (10 4898.1900452489
367.651199095 0.0) (11 4898.1900452489 294.1210972851 0.0))
((0 . "LINE") (100 . "AcDbEntity") (8 . "MASONRY") (62 . 7) (370 . 13) (100 . "AcDbLine") (10 5282.8054298643
367.651199095 0.0) (11 5282.8054298643 294.1210972851 0.0))
((0 . "LINE") (100 . "AcDbEntity") (8 . "MASONRY") (62 . 7) (370 . 13) (100 . "AcDbLine") (10 5667.4208144796
367.651199095 0.0) (11 5667.4208144796 294.1210972851 0.0))
((0 . "LINE") (100 . "AcDbEntity") (8 . "MASONRY") (62 . 7) (370 . 13) (100 . "AcDbLine") (10 6052.036199095
367.651199095 0.0) (11 6052.036199095 294.1210972851 0.0))
((0 . "LINE") (100 . "AcDbEntity") (8 . "MASONRY") (62 . 7) (370 . 13) (100 . "AcDbLine") (10 6436.6515837104
367.651199095 0.0) (11 6436.6515837104 294.1210972851 0.0))
((0 . "LINE") (100 . "AcDbEntity") (8 . "MASONRY") (62 . 7) (370 . 13) (100 . "AcDbLine") (10 6821.2669683258
367.651199095 0.0) (11 6821.2669683258 294.1210972851 0.0))
((0 . "LINE") (100 . "AcDbEntity") (8 . "MASONRY") (62 . 7) (370 . 13) (100 . "AcDbLine") (10 7205.8823529412
367.651199095 0.0) (11 7205.8823529412 294.1210972851 0.0))
((0 . "LINE") (100 . "AcDbEntity") (8 . "MASONRY") (62 . 7) (370 . 13) (100 . "AcDbLine") (10 7590.4977375566
367.651199095 0.0) (11 7590.4977375566 294.1210972851 0.0))
((0 . "LINE") (100 . "AcDbEntity") (8 . "MASONRY") (62 . 7) (370 . 13) (100 . "AcDbLine") (10 2794.1176470588
294.1210972851 0.0) (11 2975.1131221719 294.1210972851 0.0))
((0 . "LINE") (100 . "AcDbEntity") (8 . "MASONRY") (62 . 7) (370 . 13) (100 . "AcDbLine") (10 2975.1131221719
294.1210972851 0.0) (11 3167.4208144796 294.1210972851 0.0))
((0 . "LINE") (100 . "AcDbEntity") (8 . "MASONRY") (62 . 7) (370 . 13) (100 . "AcDbLine") (10 3167.4208144796
294.1210972851 0.0) (11 3359.7285067873 294.1210972851 0.0))
((0 . "LINE") (100 . "AcDbEntity") (8 . "MASONRY") (62 . 7) (370 . 13) (100 . "AcDbLine") (10 3359.7285067873
294.1210972851 0.0) (11 3552.036199095 294.1210972851 0.0))
((0 . "LINE") (100 . "AcDbEntity") (8 . "MASONRY") (62 . 7) (370 . 13) (100 . "AcDbLine") (10 3552.036199095
294.1210972851 0.0) (11 3744.3438914027 294.1210972851 0.0))
((0 . "LINE") (100 . "AcDbEntity") (8 . "MASONRY") (62 . 7) (370 . 13) (100 . "AcDbLine") (10 3744.3438914027
294.1210972851 0.0) (11 3936.6515837104 294.1210972851 0.0))
((0 . "LINE") (100 . "AcDbEntity") (8 . "MASONRY") (62 . 7) (370 . 13) (100 . "AcDbLine") (10 3936.6515837104
294.1210972851 0.0) (11 4128.9592760181 294.1210972851 0.0))
((0 . "LINE") (100 . "AcDbEntity") (8 . "MASONRY") (62 . 7) (370 . 13) (100 . "AcDbLine") (10 4128.9592760181
294.1210972851 0.0) (11 4321.2669683258 294.1210972851 0.0))
((0 . "LINE") (100 . "AcDbEntity") (8 . "MASONRY") (62 . 7) (370 . 13) (100 . "AcDbLine") (10 4321.2669683258
294.1210972851 0.0) (11 4513.5746606335 294.1210972851 0.0))
((0 . "LINE") (100 . "AcDbEntity") (8 . "MASONRY") (62 . 7) (370 . 13) (100 . "AcDbLine") (10 4513.5746606335
294.1210972851 0.0) (11 4705.8823529412 294.1210972851 0.0))
((0 . "LINE") (100 . "AcDbEntity") (8 . "MASONRY") (62 . 7) (370 . 13) (100 . "AcDbLine") (10 4705.8823529412
294.1210972851 0.0) (11 4898.1900452489 294.1210972851 0.0))
((0 . "LINE") (100 . "AcDbEntity") (8 . "MASONRY") (62 . 7) (370 . 13) (100 . "AcDbLine") (10 4898.1900452489
294.1210972851 0.0) (11 5090.4977375566 294.1210972851 0.0))
((0 . "LINE") (100 . "AcDbEntity") (8 . "MASONRY") (62 . 7) (370 . 13) (100 . "AcDbLine") (10 5090.4977375566
294.1210972851 0.0) (11 5282.8054298643 294.1210972851 0.0))
((0 . "LINE") (100 . "AcDbEntity") (8 . "MASONRY") (62 . 7) (370 . 13) (100 . "AcDbLine") (10 5282.8054298643
294.1210972851 0.0) (11 5475.1131221719 294.1210972851 0.0))
((0 . "LINE") (100 . "AcDbEntity") (8 . "MASONRY") (62 . 7) (370 . 13) (100 . "AcDbLine") (10 5475.1131221719
294.1210972851 0.0) (11 5667.4208144796 294.1210972851 0.0))
((0 . "LINE") (100 . "AcDbEntity") (8 . "MASONRY") (62 . 7) (370 . 13) (100 . "AcDbLine") (10 5667.4208144796
294.1210972851 0.0) (11 5859.7285067873 294.1210972851 0.0))
((0 . "LINE") (100 . "AcDbEntity") (8 . "MASONRY") (62 . 7) (370 . 13) (100 . "AcDbLine") (10 5859.7285067873
294.1210972851 0.0) (11 6052.036199095 294.1210972851 0.0))
((0 . "LINE") (100 . "AcDbEntity") (8 . "MASONRY") (62 . 7) (370 . 13) (100 . "AcDbLine") (10 6052.036199095
294.1210972851 0.0) (11 6244.3438914027 294.1210972851 0.0))
((0 . "LINE") (100 . "AcDbEntity") (8 . "MASONRY") (62 . 7) (370 . 13) (100 . "AcDbLine") (10 6244.3438914027
294.1210972851 0.0) (11 6436.6515837104 294.1210972851 0.0))
((0 . "LINE") (100 . "AcDbEntity") (8 . "MASONRY") (62 . 7) (370 . 13) (100 . "AcDbLine") (10 6436.6515837104
294.1210972851 0.0) (11 6628.9592760181 294.1210972851 0.0))
((0 . "LINE") (100 . "AcDbEntity") (8 . "MASONRY") (62 . 7) (370 . 13) (100 . "AcDbLine") (10 6628.9592760181
294.1210972851 0.0) (11 6821.2669683258 294.1210972851 0.0))
((0 . "LINE") (100 . "AcDbEntity") (8 . "MASONRY") (62 . 7) (370 . 13) (100 . "AcDbLine") (10 6821.2669683258
294.1210972851 0.0) (11 7013.5746606335 294.1210972851 0.0))
((0 . "LINE") (100 . "AcDbEntity") (8 . "MASONRY") (62 . 7) (370 . 13) (100 . "AcDbLine") (10 7013.5746606335
294.1210972851 0.0) (11 7205.8823529412 294.1210972851 0.0))
((0 . "LINE") (100 . "AcDbEntity") (8 . "MASONRY") (62 . 7) (370 . 13) (100 . "AcDbLine") (10 7205.8823529412
294.1210972851 0.0) (11 7398.1900452489 294.1210972851 0.0))
((0 . "LINE") (100 . "AcDbEntity") (8 . "MASONRY") (62 . 7) (370 . 13) (100 . "AcDbLine") (10 7398.1900452489
294.1210972851 0.0) (11 7590.4977375566 294.1210972851 0.0))
((0 . "LINE") (100 . "AcDbEntity") (8 . "MASONRY") (62 . 7) (370 . 13) (100 . "AcDbLine") (10 7590.4977375566
294.1210972851 0.0) (11 7782.8054298643 294.1210972851 0.0))
((0 . "LINE") (100 . "AcDbEntity") (8 . "MASONRY") (62 . 7) (370 . 13) (100 . "AcDbLine") (10 7782.8054298643
294.1210972851 0.0) (11 7860.105 294.1210972851 0.0))
((0 . "LINE") (100 . "AcDbEntity") (8 . "MASONRY") (62 . 7) (370 . 13) (100 . "AcDbLine") (10 3167.4208144796
294.1210972851 0.0) (11 3167.4208144796 225.389638009 0.0))
((0 . "LINE") (100 . "AcDbEntity") (8 . "MASONRY") (62 . 7) (370 . 13) (100 . "AcDbLine") (10 3552.036199095
294.1210972851 0.0) (11 3552.036199095 224.5349434389 0.0))
((0 . "LINE") (100 . "AcDbEntity") (8 . "MASONRY") (62 . 7) (370 . 13) (100 . "AcDbLine") (10 3936.6515837104
294.1210972851 0.0) (11 3936.6515837104 223.6802375566 0.0))
((0 . "LINE") (100 . "AcDbEntity") (8 . "MASONRY") (62 . 7) (370 . 13) (100 . "AcDbLine") (10 4321.2669683258
294.1210972851 0.0) (11 4321.2669683258 222.8255429864 0.0))
((0 . "LINE") (100 . "AcDbEntity") (8 . "MASONRY") (62 . 7) (370 . 13) (100 . "AcDbLine") (10 4705.8823529412
294.1210972851 0.0) (11 4705.8823529412 221.9708371041 0.0))
((0 . "LINE") (100 . "AcDbEntity") (8 . "MASONRY") (62 . 7) (370 . 13) (100 . "AcDbLine") (10 5090.4977375566
294.1210972851 0.0) (11 5090.4977375566 221.1161425339 0.0))
((0 . "LINE") (100 . "AcDbEntity") (8 . "MASONRY") (62 . 7) (370 . 13) (100 . "AcDbLine") (10 5475.1131221719
294.1210972851 0.0) (11 5475.1131221719 220.5909954751 0.0))
((0 . "LINE") (100 . "AcDbEntity") (8 . "MASONRY") (62 . 7) (370 . 13) (100 . "AcDbLine") (10 5859.7285067873
294.1210972851 0.0) (11 5859.7285067873 220.5909954751 0.0))
((0 . "LINE") (100 . "AcDbEntity") (8 . "MASONRY") (62 . 7) (370 . 13) (100 . "AcDbLine") (10 6244.3438914027
294.1210972851 0.0) (11 6244.3438914027 220.5909954751 0.0))
((0 . "LINE") (100 . "AcDbEntity") (8 . "MASONRY") (62 . 7) (370 . 13) (100 . "AcDbLine") (10 6628.9592760181
294.1210972851 0.0) (11 6628.9592760181 220.5909954751 0.0))
((0 . "LINE") (100 . "AcDbEntity") (8 . "MASONRY") (62 . 7) (370 . 13) (100 . "AcDbLine") (10 7013.5746606335
294.1210972851 0.0) (11 7013.5746606335 220.5909954751 0.0))
((0 . "LINE") (100 . "AcDbEntity") (8 . "MASONRY") (62 . 7) (370 . 13) (100 . "AcDbLine") (10 7398.1900452489
294.1210972851 0.0) (11 7398.1900452489 220.5909954751 0.0))
((0 . "LINE") (100 . "AcDbEntity") (8 . "MASONRY") (62 . 7) (370 . 13) (100 . "AcDbLine") (10 7782.8054298643
294.1210972851 0.0) (11 7782.8054298643 220.5909954751 0.0))
((0 . "LINE") (100 . "AcDbEntity") (8 . "MASONRY") (62 . 7) (370 . 13) (100 . "AcDbLine") (10 5326.8115045249
220.5909954751 0.0) (11 5475.1131221719 220.5909954751 0.0))
((0 . "LINE") (100 . "AcDbEntity") (8 . "MASONRY") (62 . 7) (370 . 13) (100 . "AcDbLine") (10 5475.1131221719
220.5909954751 0.0) (11 5859.7285067873 220.5909954751 0.0))
((0 . "LINE") (100 . "AcDbEntity") (8 . "MASONRY") (62 . 7) (370 . 13) (100 . "AcDbLine") (10 5859.7285067873
220.5909954751 0.0) (11 6244.3438914027 220.5909954751 0.0))
((0 . "LINE") (100 . "AcDbEntity") (8 . "MASONRY") (62 . 7) (370 . 13) (100 . "AcDbLine") (10 6244.3438914027
220.5909954751 0.0) (11 6628.9592760181 220.5909954751 0.0))
((0 . "LINE") (100 . "AcDbEntity") (8 . "MASONRY") (62 . 7) (370 . 13) (100 . "AcDbLine") (10 6628.9592760181
220.5909954751 0.0) (11 7013.5746606335 220.5909954751 0.0))
((0 . "LINE") (100 . "AcDbEntity") (8 . "MASONRY") (62 . 7) (370 . 13) (100 . "AcDbLine") (10 7013.5746606335
220.5909954751 0.0) (11 7398.1900452489 220.5909954751 0.0))
((0 . "LINE") (100 . "AcDbEntity") (8 . "MASONRY") (62 . 7) (370 . 13) (100 . "AcDbLine") (10 7398.1900452489
220.5909954751 0.0) (11 7782.8054298643 220.5909954751 0.0))
((0 . "LINE") (100 . "AcDbEntity") (8 . "MASONRY") (62 . 7) (370 . 13) (100 . "AcDbLine") (10 7782.8054298643
220.5909954751 0.0) (11 7872.3600226244 220.5909954751 0.0))
((0 . "LINE") (100 . "AcDbEntity") (8 . "MASONRY") (62 . 7) (370 . 13) (100 . "AcDbLine") (10 13390.9212104072
1180.2404072398 0.0) (11 13484.1628959276 1180.2404072398 0.0))
((0 . "LINE") (100 . "AcDbEntity") (8 . "MASONRY") (62 . 7) (370 . 13) (100 . "AcDbLine") (10 13382.3529411765
1175.2798303167 0.0) (11 13382.3529411765 1078.4318325792 0.0))
((0 . "LINE") (100 . "AcDbEntity") (8 . "MASONRY") (62 . 7) (370 . 13) (100 . "AcDbLine") (10 13305.7599434389
1078.4318325792 0.0) (11 13382.3529411765 1078.4318325792 0.0))
((0 . "LINE") (100 . "AcDbEntity") (8 . "MASONRY") (62 . 7) (370 . 13) (100 . "AcDbLine") (10 13382.3529411765
1078.4318325792 0.0) (11 13484.1628959276 1078.4318325792 0.0))
((0 . "LINE") (100 . "AcDbEntity") (8 . "MASONRY") (62 . 7) (370 . 13) (100 . "AcDbLine") (10 15712.6696832579
1078.4318325792 0.0) (11 15789.9694343891 1078.4318325792 0.0))
((0 . "LINE") (100 . "AcDbEntity") (8 . "MASONRY") (62 . 7) (370 . 13) (100 . "AcDbLine") (10 13279.8359728507
995.4751131222 0.0) (11 13382.3529411765 995.4751131222 0.0))
((0 . "LINE") (100 . "AcDbEntity") (8 . "MASONRY") (62 . 7) (370 . 13) (100 . "AcDbLine") (10 13382.3529411765
995.4751131222 0.0) (11 13484.1628959276 995.4751131222 0.0))
((0 . "LINE") (100 . "AcDbEntity") (8 . "MASONRY") (62 . 7) (370 . 13) (100 . "AcDbLine") (10 15712.6696832579
995.4751131222 0.0) (11 15862.556561086 995.4751131222 0.0))
((0 . "LINE") (100 . "AcDbEntity") (8 . "MASONRY") (62 . 7) (370 . 13) (100 . "AcDbLine") (10 13382.3529411765
995.4751131222 0.0) (11 13382.3529411765 961.5384615385 0.0))
((0 . "LINE") (100 . "AcDbEntity") (8 . "MASONRY") (62 . 7) (370 . 13) (100 . "AcDbLine") (10 12592.3827828054
865.3832352941 0.0) (11 12613.1221719457 865.3832352941 0.0))
((0 . "LINE") (100 . "AcDbEntity") (8 . "MASONRY") (62 . 7) (370 . 13) (100 . "AcDbLine") (10 12613.1221719457
865.3832352941 0.0) (11 12616.8284276018 865.3832352941 0.0))
((0 . "LINE") (100 . "AcDbEntity") (8 . "MASONRY") (62 . 7) (370 . 13) (100 . "AcDbLine") (10 16678.7865723982
865.3832352941 0.0) (11 16698.5735520362 865.3832352941 0.0))
((0 . "LINE") (100 . "AcDbEntity") (8 . "MASONRY") (62 . 7) (370 . 13) (100 . "AcDbLine") (10 12613.1221719457
865.3832352941 0.0) (11 12613.1221719457 791.8552036199 0.0))
((0 . "LINE") (100 . "AcDbEntity") (8 . "MASONRY") (62 . 7) (370 . 13) (100 . "AcDbLine") (10 16459.2760180996
845.7545927602 0.0) (11 16459.2760180996 791.8552036199 0.0))
((0 . "LINE") (100 . "AcDbEntity") (8 . "MASONRY") (62 . 7) (370 . 13) (100 . "AcDbLine") (10 12340.848800905
791.8552036199 0.0) (11 12406.988438914 791.8552036199 0.0))
((0 . "LINE") (100 . "AcDbEntity") (8 . "MASONRY") (62 . 7) (370 . 13) (100 . "AcDbLine") (10 12574.8761085973
791.8552036199 0.0) (11 12613.1221719457 791.8552036199 0.0))
((0 . "LINE") (100 . "AcDbEntity") (8 . "MASONRY") (62 . 7) (370 . 13) (100 . "AcDbLine") (10 12613.1221719457
791.8552036199 0.0) (11 12644.7183597285 791.8552036199 0.0))
((0 . "LINE") (100 . "AcDbEntity") (8 . "MASONRY") (62 . 7) (370 . 13) (100 . "AcDbLine") (10 12890.0021493213
791.8552036199 0.0) (11 12904.007760181 791.8552036199 0.0))
((0 . "LINE") (100 . "AcDbEntity") (8 . "MASONRY") (62 . 7) (370 . 13) (100 . "AcDbLine") (10 16412.0767647059
791.8552036199 0.0) (11 16459.2760180996 791.8552036199 0.0))
((0 . "LINE") (100 . "AcDbEntity") (8 . "MASONRY") (62 . 7) (370 . 13) (100 . "AcDbLine") (10 16459.2760180996
791.8552036199 0.0) (11 16507.5017873303 791.8552036199 0.0))
((0 . "LINE") (100 . "AcDbEntity") (8 . "MASONRY") (62 . 7) (370 . 13) (100 . "AcDbLine") (10 16661.27989819
791.8552036199 0.0) (11 16732.5095701357 791.8552036199 0.0))
((0 . "LINE") (100 . "AcDbEntity") (8 . "MASONRY") (62 . 7) (370 . 13) (100 . "AcDbLine") (10 16940.3145927602
791.8552036199 0.0) (11 16968.3257918552 791.8552036199 0.0))
((0 . "LINE") (100 . "AcDbEntity") (8 . "MASONRY") (62 . 7) (370 . 13) (100 . "AcDbLine") (10 12420.814479638
779.4117647059 0.0) (11 12420.814479638 727.6778393665 0.0))
((0 . "LINE") (100 . "AcDbEntity") (8 . "MASONRY") (62 . 7) (370 . 13) (100 . "AcDbLine") (10 16651.5837104072
751.1312217195 0.0) (11 16651.5837104072 727.6778393665 0.0))
((0 . "LINE") (100 . "AcDbEntity") (8 . "MASONRY") (62 . 7) (370 . 13) (100 . "AcDbLine") (10 12358.5529072398
727.6778393665 0.0) (11 12420.814479638 727.6778393665 0.0))
((0 . "LINE") (100 . "AcDbEntity") (8 . "MASONRY") (62 . 7) (370 . 13) (100 . "AcDbLine") (10 12420.814479638
727.6778393665 0.0) (11 12478.2966176471 727.6778393665 0.0))
((0 . "LINE") (100 . "AcDbEntity") (8 . "MASONRY") (62 . 7) (370 . 13) (100 . "AcDbLine") (10 12559.595780543
727.6778393665 0.0) (11 12613.1221719457 727.6778393665 0.0))
((0 . "LINE") (100 . "AcDbEntity") (8 . "MASONRY") (62 . 7) (370 . 13) (100 . "AcDbLine") (10 12613.1221719457
727.6778393665 0.0) (11 12669.0615045249 727.6778393665 0.0))
((0 . "LINE") (100 . "AcDbEntity") (8 . "MASONRY") (62 . 7) (370 . 13) (100 . "AcDbLine") (10 12841.1051131222
727.6778393665 0.0) (11 12894.8395588235 727.6778393665 0.0))
((0 . "LINE") (100 . "AcDbEntity") (8 . "MASONRY") (62 . 7) (370 . 13) (100 . "AcDbLine") (10 16392.1596493213
727.6778393665 0.0) (11 16459.2760180996 727.6778393665 0.0))
((0 . "LINE") (100 . "AcDbEntity") (8 . "MASONRY") (62 . 7) (370 . 13) (100 . "AcDbLine") (10 16459.2760180996
727.6778393665 0.0) (11 16564.9236312217 727.6778393665 0.0))
((0 . "LINE") (100 . "AcDbEntity") (8 . "MASONRY") (62 . 7) (370 . 13) (100 . "AcDbLine") (10 16645.9995701357
727.6778393665 0.0) (11 16651.5837104072 727.6778393665 0.0))
((0 . "LINE") (100 . "AcDbEntity") (8 . "MASONRY") (62 . 7) (370 . 13) (100 . "AcDbLine") (10 16651.5837104072
727.6778393665 0.0) (11 16762.12989819 727.6778393665 0.0))
((0 . "LINE") (100 . "AcDbEntity") (8 . "MASONRY") (62 . 7) (370 . 13) (100 . "AcDbLine") (10 16900.5857466063
727.6778393665 0.0) (11 16968.3257918552 727.6778393665 0.0))
((0 . "LINE") (100 . "AcDbEntity") (8 . "MASONRY") (62 . 7) (370 . 13) (100 . "AcDbLine") (10 12613.1221719457
727.6778393665 0.0) (11 12613.1221719457 563.5436764706 0.0))
((0 . "LINE") (100 . "AcDbEntity") (8 . "MASONRY") (62 . 7) (370 . 13) (100 . "AcDbLine") (10 16459.2760180996
727.6778393665 0.0) (11 16459.2760180996 563.5436764706 0.0))
((0 . "LINE") (100 . "AcDbEntity") (8 . "MASONRY") (62 . 7) (370 . 13) (100 . "AcDbLine") (10 16843.8914027149
636.0946719457 0.0) (11 16843.8914027149 563.5436764706 0.0))
((0 . "LINE") (100 . "AcDbEntity") (8 . "MASONRY") (62 . 7) (370 . 13) (100 . "AcDbLine") (10 12403.831300905
563.5436764706 0.0) (11 12420.814479638 563.5436764706 0.0))
((0 . "LINE") (100 . "AcDbEntity") (8 . "MASONRY") (62 . 7) (370 . 13) (100 . "AcDbLine") (10 12420.814479638
563.5436764706 0.0) (11 12613.1221719457 563.5436764706 0.0))
((0 . "LINE") (100 . "AcDbEntity") (8 . "MASONRY") (62 . 7) (370 . 13) (100 . "AcDbLine") (10 12613.1221719457
563.5436764706 0.0) (11 12805.4298642534 563.5436764706 0.0))
((0 . "LINE") (100 . "AcDbEntity") (8 . "MASONRY") (62 . 7) (370 . 13) (100 . "AcDbLine") (10 12805.4298642534
563.5436764706 0.0) (11 12871.391821267 563.5436764706 0.0))
((0 . "LINE") (100 . "AcDbEntity") (8 . "MASONRY") (62 . 7) (370 . 13) (100 . "AcDbLine") (10 13273.7863122172
563.5436764706 0.0) (11 13373.7969683258 563.5436764706 0.0))
((0 . "LINE") (100 . "AcDbEntity") (8 . "MASONRY") (62 . 7) (370 . 13) (100 . "AcDbLine") (10 15317.9586425339
563.5436764706 0.0) (11 15372.071719457 563.5436764706 0.0))
((0 . "LINE") (100 . "AcDbEntity") (8 . "MASONRY") (62 . 7) (370 . 13) (100 . "AcDbLine") (10 15864.5807692308
563.5436764706 0.0) (11 15876.0938461538 563.5436764706 0.0))
((0 . "LINE") (100 . "AcDbEntity") (8 . "MASONRY") (62 . 7) (370 . 13) (100 . "AcDbLine") (10 16341.221459276
563.5436764706 0.0) (11 16459.2760180996 563.5436764706 0.0))
((0 . "LINE") (100 . "AcDbEntity") (8 . "MASONRY") (62 . 7) (370 . 13) (100 . "AcDbLine") (10 16459.2760180996
563.5436764706 0.0) (11 16651.5837104072 563.5436764706 0.0))
((0 . "LINE") (100 . "AcDbEntity") (8 . "MASONRY") (62 . 7) (370 . 13) (100 . "AcDbLine") (10 16651.5837104072
563.5436764706 0.0) (11 16843.8914027149 563.5436764706 0.0))
((0 . "LINE") (100 . "AcDbEntity") (8 . "MASONRY") (62 . 7) (370 . 13) (100 . "AcDbLine") (10 16843.8914027149
563.5436764706 0.0) (11 16968.3257918552 563.5436764706 0.0))
((0 . "LINE") (100 . "AcDbEntity") (8 . "MASONRY") (62 . 7) (370 . 13) (100 . "AcDbLine") (10 12420.814479638
563.5436764706 0.0) (11 12420.814479638 488.9937895928 0.0))
((0 . "LINE") (100 . "AcDbEntity") (8 . "MASONRY") (62 . 7) (370 . 13) (100 . "AcDbLine") (10 12805.4298642534
563.5436764706 0.0) (11 12805.4298642534 488.9937895928 0.0))
((0 . "LINE") (100 . "AcDbEntity") (8 . "MASONRY") (62 . 7) (370 . 13) (100 . "AcDbLine") (10 13190.0452488688
505.5690950226 0.0) (11 13190.0452488688 488.9937895928 0.0))
((0 . "LINE") (100 . "AcDbEntity") (8 . "MASONRY") (62 . 7) (370 . 13) (100 . "AcDbLine") (10 14343.8914027149
526.9932918552 0.0) (11 14343.8914027149 488.9937895928 0.0))
((0 . "LINE") (100 . "AcDbEntity") (8 . "MASONRY") (62 . 7) (370 . 13) (100 . "AcDbLine") (10 14728.5067873303
524.5296493213 0.0) (11 14728.5067873303 488.9937895928 0.0))
((0 . "LINE") (100 . "AcDbEntity") (8 . "MASONRY") (62 . 7) (370 . 13) (100 . "AcDbLine") (10 15497.7375565611
512.1349208145 0.0) (11 15497.7375565611 488.9937895928 0.0))
((0 . "LINE") (100 . "AcDbEntity") (8 . "MASONRY") (62 . 7) (370 . 13) (100 . "AcDbLine") (10 15882.3529411765
560.9831334842 0.0) (11 15882.3529411765 488.9937895928 0.0))
((0 . "LINE") (100 . "AcDbEntity") (8 . "MASONRY") (62 . 7) (370 . 13) (100 . "AcDbLine") (10 16266.9683257919
517.9804751131 0.0) (11 16266.9683257919 488.9937895928 0.0))
((0 . "LINE") (100 . "AcDbEntity") (8 . "MASONRY") (62 . 7) (370 . 13) (100 . "AcDbLine") (10 16651.5837104072
563.5436764706 0.0) (11 16651.5837104072 488.9937895928 0.0))
((0 . "LINE") (100 . "AcDbEntity") (8 . "MASONRY") (62 . 7) (370 . 13) (100 . "AcDbLine") (10 12167.1198190045
488.9937895928 0.0) (11 12228.5067873303 488.9937895928 0.0))
((0 . "LINE") (100 . "AcDbEntity") (8 . "MASONRY") (62 . 7) (370 . 13) (100 . "AcDbLine") (10 12228.5067873303
488.9937895928 0.0) (11 12420.814479638 488.9937895928 0.0))
((0 . "LINE") (100 . "AcDbEntity") (8 . "MASONRY") (62 . 7) (370 . 13) (100 . "AcDbLine") (10 12420.814479638
488.9937895928 0.0) (11 12613.1221719457 488.9937895928 0.0))
((0 . "LINE") (100 . "AcDbEntity") (8 . "MASONRY") (62 . 7) (370 . 13) (100 . "AcDbLine") (10 12613.1221719457
488.9937895928 0.0) (11 12805.4298642534 488.9937895928 0.0))
((0 . "LINE") (100 . "AcDbEntity") (8 . "MASONRY") (62 . 7) (370 . 13) (100 . "AcDbLine") (10 12805.4298642534
488.9937895928 0.0) (11 12997.7375565611 488.9937895928 0.0))
((0 . "LINE") (100 . "AcDbEntity") (8 . "MASONRY") (62 . 7) (370 . 13) (100 . "AcDbLine") (10 12997.7375565611
488.9937895928 0.0) (11 13190.0452488688 488.9937895928 0.0))
((0 . "LINE") (100 . "AcDbEntity") (8 . "MASONRY") (62 . 7) (370 . 13) (100 . "AcDbLine") (10 13190.0452488688
488.9937895928 0.0) (11 13382.3529411765 488.9937895928 0.0))
((0 . "LINE") (100 . "AcDbEntity") (8 . "MASONRY") (62 . 7) (370 . 13) (100 . "AcDbLine") (10 13382.3529411765
488.9937895928 0.0) (11 13473.196821267 488.9937895928 0.0))
((0 . "LINE") (100 . "AcDbEntity") (8 . "MASONRY") (62 . 7) (370 . 13) (100 . "AcDbLine") (10 13557.1730995475
488.9937895928 0.0) (11 13766.9683257919 488.9937895928 0.0))
((0 . "LINE") (100 . "AcDbEntity") (8 . "MASONRY") (62 . 7) (370 . 13) (100 . "AcDbLine") (10 13766.9683257919
488.9937895928 0.0) (11 13894.2882126697 488.9937895928 0.0))
((0 . "LINE") (100 . "AcDbEntity") (8 . "MASONRY") (62 . 7) (370 . 13) (100 . "AcDbLine") (10 14065.8621832579
488.9937895928 0.0) (11 14151.5837104072 488.9937895928 0.0))
((0 . "LINE") (100 . "AcDbEntity") (8 . "MASONRY") (62 . 7) (370 . 13) (100 . "AcDbLine") (10 14151.5837104072
488.9937895928 0.0) (11 14343.8914027149 488.9937895928 0.0))
((0 . "LINE") (100 . "AcDbEntity") (8 . "MASONRY") (62 . 7) (370 . 13) (100 . "AcDbLine") (10 14343.8914027149
488.9937895928 0.0) (11 14444.0719117647 488.9937895928 0.0))
((0 . "LINE") (100 . "AcDbEntity") (8 . "MASONRY") (62 . 7) (370 . 13) (100 . "AcDbLine") (10 14660.9886425339
488.9937895928 0.0) (11 14728.5067873303 488.9937895928 0.0))
((0 . "LINE") (100 . "AcDbEntity") (8 . "MASONRY") (62 . 7) (370 . 13) (100 . "AcDbLine") (10 14728.5067873303
488.9937895928 0.0) (11 14920.814479638 488.9937895928 0.0))
((0 . "LINE") (100 . "AcDbEntity") (8 . "MASONRY") (62 . 7) (370 . 13) (100 . "AcDbLine") (10 14920.814479638
488.9937895928 0.0) (11 14961.3909841629 488.9937895928 0.0))
((0 . "LINE") (100 . "AcDbEntity") (8 . "MASONRY") (62 . 7) (370 . 13) (100 . "AcDbLine") (10 15178.1628167421
488.9937895928 0.0) (11 15305.4298642534 488.9937895928 0.0))
((0 . "LINE") (100 . "AcDbEntity") (8 . "MASONRY") (62 . 7) (370 . 13) (100 . "AcDbLine") (10 15305.4298642534
488.9937895928 0.0) (11 15497.7375565611 488.9937895928 0.0))
((0 . "LINE") (100 . "AcDbEntity") (8 . "MASONRY") (62 . 7) (370 . 13) (100 . "AcDbLine") (10 15497.7375565611
488.9937895928 0.0) (11 15554.3047850679 488.9937895928 0.0))
((0 . "LINE") (100 . "AcDbEntity") (8 . "MASONRY") (62 . 7) (370 . 13) (100 . "AcDbLine") (10 15631.6123755656
488.9937895928 0.0) (11 15690.0452488688 488.9937895928 0.0))
((0 . "LINE") (100 . "AcDbEntity") (8 . "MASONRY") (62 . 7) (370 . 13) (100 . "AcDbLine") (10 15690.0452488688
488.9937895928 0.0) (11 15882.3529411765 488.9937895928 0.0))
((0 . "LINE") (100 . "AcDbEntity") (8 . "MASONRY") (62 . 7) (370 . 13) (100 . "AcDbLine") (10 15882.3529411765
488.9937895928 0.0) (11 16058.3269004525 488.9937895928 0.0))
((0 . "LINE") (100 . "AcDbEntity") (8 . "MASONRY") (62 . 7) (370 . 13) (100 . "AcDbLine") (10 16188.2901809955
488.9937895928 0.0) (11 16266.9683257919 488.9937895928 0.0))
((0 . "LINE") (100 . "AcDbEntity") (8 . "MASONRY") (62 . 7) (370 . 13) (100 . "AcDbLine") (10 16266.9683257919
488.9937895928 0.0) (11 16459.2760180996 488.9937895928 0.0))
((0 . "LINE") (100 . "AcDbEntity") (8 . "MASONRY") (62 . 7) (370 . 13) (100 . "AcDbLine") (10 16459.2760180996
488.9937895928 0.0) (11 16651.5837104072 488.9937895928 0.0))
((0 . "LINE") (100 . "AcDbEntity") (8 . "MASONRY") (62 . 7) (370 . 13) (100 . "AcDbLine") (10 16651.5837104072
488.9937895928 0.0) (11 16843.8914027149 488.9937895928 0.0))
((0 . "LINE") (100 . "AcDbEntity") (8 . "MASONRY") (62 . 7) (370 . 13) (100 . "AcDbLine") (10 16843.8914027149
488.9937895928 0.0) (11 16968.3257918552 488.9937895928 0.0))
((0 . "LINE") (100 . "AcDbEntity") (8 . "MASONRY") (62 . 7) (370 . 13) (100 . "AcDbLine") (10 12228.5067873303
488.9937895928 0.0) (11 12228.5067873303 414.4439027149 0.0))
((0 . "LINE") (100 . "AcDbEntity") (8 . "MASONRY") (62 . 7) (370 . 13) (100 . "AcDbLine") (10 12613.1221719457
488.9937895928 0.0) (11 12613.1221719457 414.4439027149 0.0))
((0 . "LINE") (100 . "AcDbEntity") (8 . "MASONRY") (62 . 7) (370 . 13) (100 . "AcDbLine") (10 12997.7375565611
488.9937895928 0.0) (11 12997.7375565611 414.4439027149 0.0))
((0 . "LINE") (100 . "AcDbEntity") (8 . "MASONRY") (62 . 7) (370 . 13) (100 . "AcDbLine") (10 13382.3529411765
488.9937895928 0.0) (11 13382.3529411765 414.4439027149 0.0))
((0 . "LINE") (100 . "AcDbEntity") (8 . "MASONRY") (62 . 7) (370 . 13) (100 . "AcDbLine") (10 13766.9683257919
488.9937895928 0.0) (11 13766.9683257919 414.4439027149 0.0))
((0 . "LINE") (100 . "AcDbEntity") (8 . "MASONRY") (62 . 7) (370 . 13) (100 . "AcDbLine") (10 14151.5837104072
488.9937895928 0.0) (11 14151.5837104072 414.4439027149 0.0))
((0 . "LINE") (100 . "AcDbEntity") (8 . "MASONRY") (62 . 7) (370 . 13) (100 . "AcDbLine") (10 14536.1990950226
454.0489932127 0.0) (11 14536.1990950226 414.4439027149 0.0))
((0 . "LINE") (100 . "AcDbEntity") (8 . "MASONRY") (62 . 7) (370 . 13) (100 . "AcDbLine") (10 14920.814479638
488.9937895928 0.0) (11 14920.814479638 414.4439027149 0.0))
((0 . "LINE") (100 . "AcDbEntity") (8 . "MASONRY") (62 . 7) (370 . 13) (100 . "AcDbLine") (10 15305.4298642534
488.9937895928 0.0) (11 15305.4298642534 414.4439027149 0.0))
((0 . "LINE") (100 . "AcDbEntity") (8 . "MASONRY") (62 . 7) (370 . 13) (100 . "AcDbLine") (10 15690.0452488688
488.9937895928 0.0) (11 15690.0452488688 414.4439027149 0.0))
((0 . "LINE") (100 . "AcDbEntity") (8 . "MASONRY") (62 . 7) (370 . 13) (100 . "AcDbLine") (10 16074.6606334842
482.3118099548 0.0) (11 16074.6606334842 414.4439027149 0.0))
((0 . "LINE") (100 . "AcDbEntity") (8 . "MASONRY") (62 . 7) (370 . 13) (100 . "AcDbLine") (10 16459.2760180996
488.9937895928 0.0) (11 16459.2760180996 414.4439027149 0.0))
((0 . "LINE") (100 . "AcDbEntity") (8 . "MASONRY") (62 . 7) (370 . 13) (100 . "AcDbLine") (10 16843.8914027149
488.9937895928 0.0) (11 16843.8914027149 414.4439027149 0.0))
((0 . "LINE") (100 . "AcDbEntity") (8 . "MASONRY") (62 . 7) (370 . 13) (100 . "AcDbLine") (10 12155.6506108597
414.4439027149 0.0) (11 12228.5067873303 414.4439027149 0.0))
((0 . "LINE") (100 . "AcDbEntity") (8 . "MASONRY") (62 . 7) (370 . 13) (100 . "AcDbLine") (10 12228.5067873303
414.4439027149 0.0) (11 12420.814479638 414.4439027149 0.0))
((0 . "LINE") (100 . "AcDbEntity") (8 . "MASONRY") (62 . 7) (370 . 13) (100 . "AcDbLine") (10 12420.814479638
414.4439027149 0.0) (11 12613.1221719457 414.4439027149 0.0))
((0 . "LINE") (100 . "AcDbEntity") (8 . "MASONRY") (62 . 7) (370 . 13) (100 . "AcDbLine") (10 12613.1221719457
414.4439027149 0.0) (11 12805.4298642534 414.4439027149 0.0))
((0 . "LINE") (100 . "AcDbEntity") (8 . "MASONRY") (62 . 7) (370 . 13) (100 . "AcDbLine") (10 12805.4298642534
414.4439027149 0.0) (11 12997.7375565611 414.4439027149 0.0))
((0 . "LINE") (100 . "AcDbEntity") (8 . "MASONRY") (62 . 7) (370 . 13) (100 . "AcDbLine") (10 12997.7375565611
414.4439027149 0.0) (11 13190.0452488688 414.4439027149 0.0))
((0 . "LINE") (100 . "AcDbEntity") (8 . "MASONRY") (62 . 7) (370 . 13) (100 . "AcDbLine") (10 13190.0452488688
414.4439027149 0.0) (11 13382.3529411765 414.4439027149 0.0))
((0 . "LINE") (100 . "AcDbEntity") (8 . "MASONRY") (62 . 7) (370 . 13) (100 . "AcDbLine") (10 13382.3529411765
414.4439027149 0.0) (11 13574.6606334842 414.4439027149 0.0))
((0 . "LINE") (100 . "AcDbEntity") (8 . "MASONRY") (62 . 7) (370 . 13) (100 . "AcDbLine") (10 13574.6606334842
414.4439027149 0.0) (11 13766.9683257919 414.4439027149 0.0))
((0 . "LINE") (100 . "AcDbEntity") (8 . "MASONRY") (62 . 7) (370 . 13) (100 . "AcDbLine") (10 13766.9683257919
414.4439027149 0.0) (11 13959.2760180995 414.4439027149 0.0))
((0 . "LINE") (100 . "AcDbEntity") (8 . "MASONRY") (62 . 7) (370 . 13) (100 . "AcDbLine") (10 13959.2760180995
414.4439027149 0.0) (11 14151.5837104072 414.4439027149 0.0))
((0 . "LINE") (100 . "AcDbEntity") (8 . "MASONRY") (62 . 7) (370 . 13) (100 . "AcDbLine") (10 14151.5837104072
414.4439027149 0.0) (11 14343.8914027149 414.4439027149 0.0))
((0 . "LINE") (100 . "AcDbEntity") (8 . "MASONRY") (62 . 7) (370 . 13) (100 . "AcDbLine") (10 14343.8914027149
414.4439027149 0.0) (11 14536.1990950226 414.4439027149 0.0))
((0 . "LINE") (100 . "AcDbEntity") (8 . "MASONRY") (62 . 7) (370 . 13) (100 . "AcDbLine") (10 14536.1990950226
414.4439027149 0.0) (11 14728.5067873303 414.4439027149 0.0))
((0 . "LINE") (100 . "AcDbEntity") (8 . "MASONRY") (62 . 7) (370 . 13) (100 . "AcDbLine") (10 14728.5067873303
414.4439027149 0.0) (11 14920.814479638 414.4439027149 0.0))
((0 . "LINE") (100 . "AcDbEntity") (8 . "MASONRY") (62 . 7) (370 . 13) (100 . "AcDbLine") (10 14920.814479638
414.4439027149 0.0) (11 15113.1221719457 414.4439027149 0.0))
((0 . "LINE") (100 . "AcDbEntity") (8 . "MASONRY") (62 . 7) (370 . 13) (100 . "AcDbLine") (10 15113.1221719457
414.4439027149 0.0) (11 15305.4298642534 414.4439027149 0.0))
((0 . "LINE") (100 . "AcDbEntity") (8 . "MASONRY") (62 . 7) (370 . 13) (100 . "AcDbLine") (10 15305.4298642534
414.4439027149 0.0) (11 15497.7375565611 414.4439027149 0.0))
((0 . "LINE") (100 . "AcDbEntity") (8 . "MASONRY") (62 . 7) (370 . 13) (100 . "AcDbLine") (10 15497.7375565611
414.4439027149 0.0) (11 15690.0452488688 414.4439027149 0.0))
((0 . "LINE") (100 . "AcDbEntity") (8 . "MASONRY") (62 . 7) (370 . 13) (100 . "AcDbLine") (10 15690.0452488688
414.4439027149 0.0) (11 15882.3529411765 414.4439027149 0.0))
((0 . "LINE") (100 . "AcDbEntity") (8 . "MASONRY") (62 . 7) (370 . 13) (100 . "AcDbLine") (10 15882.3529411765
414.4439027149 0.0) (11 16074.6606334842 414.4439027149 0.0))
((0 . "LINE") (100 . "AcDbEntity") (8 . "MASONRY") (62 . 7) (370 . 13) (100 . "AcDbLine") (10 16074.6606334842
414.4439027149 0.0) (11 16266.9683257919 414.4439027149 0.0))
((0 . "LINE") (100 . "AcDbEntity") (8 . "MASONRY") (62 . 7) (370 . 13) (100 . "AcDbLine") (10 16266.9683257919
414.4439027149 0.0) (11 16459.2760180996 414.4439027149 0.0))
((0 . "LINE") (100 . "AcDbEntity") (8 . "MASONRY") (62 . 7) (370 . 13) (100 . "AcDbLine") (10 16459.2760180996
414.4439027149 0.0) (11 16651.5837104072 414.4439027149 0.0))
((0 . "LINE") (100 . "AcDbEntity") (8 . "MASONRY") (62 . 7) (370 . 13) (100 . "AcDbLine") (10 16651.5837104072
414.4439027149 0.0) (11 16843.8914027149 414.4439027149 0.0))
((0 . "LINE") (100 . "AcDbEntity") (8 . "MASONRY") (62 . 7) (370 . 13) (100 . "AcDbLine") (10 16843.8914027149
414.4439027149 0.0) (11 17036.1990950226 414.4439027149 0.0))
((0 . "LINE") (100 . "AcDbEntity") (8 . "MASONRY") (62 . 7) (370 . 13) (100 . "AcDbLine") (10 17036.1990950226
414.4439027149 0.0) (11 17183.9426131222 414.4439027149 0.0))
((0 . "LINE") (100 . "AcDbEntity") (8 . "MASONRY") (62 . 7) (370 . 13) (100 . "AcDbLine") (10 12420.814479638
414.4439027149 0.0) (11 12420.814479638 339.8940158371 0.0))
((0 . "LINE") (100 . "AcDbEntity") (8 . "MASONRY") (62 . 7) (370 . 13) (100 . "AcDbLine") (10 12805.4298642534
414.4439027149 0.0) (11 12805.4298642534 339.8940158371 0.0))
((0 . "LINE") (100 . "AcDbEntity") (8 . "MASONRY") (62 . 7) (370 . 13) (100 . "AcDbLine") (10 13190.0452488688
414.4439027149 0.0) (11 13190.0452488688 339.8940158371 0.0))
((0 . "LINE") (100 . "AcDbEntity") (8 . "MASONRY") (62 . 7) (370 . 13) (100 . "AcDbLine") (10 13574.6606334842
414.4439027149 0.0) (11 13574.6606334842 339.8940158371 0.0))
((0 . "LINE") (100 . "AcDbEntity") (8 . "MASONRY") (62 . 7) (370 . 13) (100 . "AcDbLine") (10 13959.2760180995
414.4439027149 0.0) (11 13959.2760180995 339.8940158371 0.0))
((0 . "LINE") (100 . "AcDbEntity") (8 . "MASONRY") (62 . 7) (370 . 13) (100 . "AcDbLine") (10 14343.8914027149
414.4439027149 0.0) (11 14343.8914027149 339.8940158371 0.0))
((0 . "LINE") (100 . "AcDbEntity") (8 . "MASONRY") (62 . 7) (370 . 13) (100 . "AcDbLine") (10 14728.5067873303
414.4439027149 0.0) (11 14728.5067873303 339.8940158371 0.0))
((0 . "LINE") (100 . "AcDbEntity") (8 . "MASONRY") (62 . 7) (370 . 13) (100 . "AcDbLine") (10 15113.1221719457
414.4439027149 0.0) (11 15113.1221719457 339.8940158371 0.0))
((0 . "LINE") (100 . "AcDbEntity") (8 . "MASONRY") (62 . 7) (370 . 13) (100 . "AcDbLine") (10 15497.7375565611
414.4439027149 0.0) (11 15497.7375565611 339.8940158371 0.0))
((0 . "LINE") (100 . "AcDbEntity") (8 . "MASONRY") (62 . 7) (370 . 13) (100 . "AcDbLine") (10 15882.3529411765
414.4439027149 0.0) (11 15882.3529411765 339.8940158371 0.0))
((0 . "LINE") (100 . "AcDbEntity") (8 . "MASONRY") (62 . 7) (370 . 13) (100 . "AcDbLine") (10 16266.9683257919
414.4439027149 0.0) (11 16266.9683257919 339.8940158371 0.0))
((0 . "LINE") (100 . "AcDbEntity") (8 . "MASONRY") (62 . 7) (370 . 13) (100 . "AcDbLine") (10 16651.5837104072
414.4439027149 0.0) (11 16651.5837104072 339.8940158371 0.0))
((0 . "LINE") (100 . "AcDbEntity") (8 . "MASONRY") (62 . 7) (370 . 13) (100 . "AcDbLine") (10 17036.1990950226
414.4439027149 0.0) (11 17036.1990950226 339.8940158371 0.0))
((0 . "LINE") (100 . "AcDbEntity") (8 . "MASONRY") (62 . 7) (370 . 13) (100 . "AcDbLine") (10 12144.1814027149
339.8940158371 0.0) (11 12228.5067873303 339.8940158371 0.0))
((0 . "LINE") (100 . "AcDbEntity") (8 . "MASONRY") (62 . 7) (370 . 13) (100 . "AcDbLine") (10 12228.5067873303
339.8940158371 0.0) (11 12420.814479638 339.8940158371 0.0))
((0 . "LINE") (100 . "AcDbEntity") (8 . "MASONRY") (62 . 7) (370 . 13) (100 . "AcDbLine") (10 12420.814479638
339.8940158371 0.0) (11 12613.1221719457 339.8940158371 0.0))
((0 . "LINE") (100 . "AcDbEntity") (8 . "MASONRY") (62 . 7) (370 . 13) (100 . "AcDbLine") (10 12613.1221719457
339.8940158371 0.0) (11 12805.4298642534 339.8940158371 0.0))
((0 . "LINE") (100 . "AcDbEntity") (8 . "MASONRY") (62 . 7) (370 . 13) (100 . "AcDbLine") (10 12805.4298642534
339.8940158371 0.0) (11 12997.7375565611 339.8940158371 0.0))
((0 . "LINE") (100 . "AcDbEntity") (8 . "MASONRY") (62 . 7) (370 . 13) (100 . "AcDbLine") (10 12997.7375565611
339.8940158371 0.0) (11 13190.0452488688 339.8940158371 0.0))
((0 . "LINE") (100 . "AcDbEntity") (8 . "MASONRY") (62 . 7) (370 . 13) (100 . "AcDbLine") (10 13190.0452488688
339.8940158371 0.0) (11 13382.3529411765 339.8940158371 0.0))
((0 . "LINE") (100 . "AcDbEntity") (8 . "MASONRY") (62 . 7) (370 . 13) (100 . "AcDbLine") (10 13382.3529411765
339.8940158371 0.0) (11 13574.6606334842 339.8940158371 0.0))
((0 . "LINE") (100 . "AcDbEntity") (8 . "MASONRY") (62 . 7) (370 . 13) (100 . "AcDbLine") (10 13574.6606334842
339.8940158371 0.0) (11 13766.9683257919 339.8940158371 0.0))
((0 . "LINE") (100 . "AcDbEntity") (8 . "MASONRY") (62 . 7) (370 . 13) (100 . "AcDbLine") (10 13766.9683257919
339.8940158371 0.0) (11 13959.2760180995 339.8940158371 0.0))
((0 . "LINE") (100 . "AcDbEntity") (8 . "MASONRY") (62 . 7) (370 . 13) (100 . "AcDbLine") (10 13959.2760180995
339.8940158371 0.0) (11 14151.5837104072 339.8940158371 0.0))
((0 . "LINE") (100 . "AcDbEntity") (8 . "MASONRY") (62 . 7) (370 . 13) (100 . "AcDbLine") (10 14151.5837104072
339.8940158371 0.0) (11 14343.8914027149 339.8940158371 0.0))
((0 . "LINE") (100 . "AcDbEntity") (8 . "MASONRY") (62 . 7) (370 . 13) (100 . "AcDbLine") (10 14343.8914027149
339.8940158371 0.0) (11 14536.1990950226 339.8940158371 0.0))
((0 . "LINE") (100 . "AcDbEntity") (8 . "MASONRY") (62 . 7) (370 . 13) (100 . "AcDbLine") (10 14536.1990950226
339.8940158371 0.0) (11 14728.5067873303 339.8940158371 0.0))
((0 . "LINE") (100 . "AcDbEntity") (8 . "MASONRY") (62 . 7) (370 . 13) (100 . "AcDbLine") (10 14728.5067873303
339.8940158371 0.0) (11 14920.814479638 339.8940158371 0.0))
((0 . "LINE") (100 . "AcDbEntity") (8 . "MASONRY") (62 . 7) (370 . 13) (100 . "AcDbLine") (10 14920.814479638
339.8940158371 0.0) (11 15113.1221719457 339.8940158371 0.0))
((0 . "LINE") (100 . "AcDbEntity") (8 . "MASONRY") (62 . 7) (370 . 13) (100 . "AcDbLine") (10 15113.1221719457
339.8940158371 0.0) (11 15305.4298642534 339.8940158371 0.0))
((0 . "LINE") (100 . "AcDbEntity") (8 . "MASONRY") (62 . 7) (370 . 13) (100 . "AcDbLine") (10 15305.4298642534
339.8940158371 0.0) (11 15497.7375565611 339.8940158371 0.0))
((0 . "LINE") (100 . "AcDbEntity") (8 . "MASONRY") (62 . 7) (370 . 13) (100 . "AcDbLine") (10 15497.7375565611
339.8940158371 0.0) (11 15690.0452488688 339.8940158371 0.0))
((0 . "LINE") (100 . "AcDbEntity") (8 . "MASONRY") (62 . 7) (370 . 13) (100 . "AcDbLine") (10 15690.0452488688
339.8940158371 0.0) (11 15882.3529411765 339.8940158371 0.0))
((0 . "LINE") (100 . "AcDbEntity") (8 . "MASONRY") (62 . 7) (370 . 13) (100 . "AcDbLine") (10 15882.3529411765
339.8940158371 0.0) (11 16074.6606334842 339.8940158371 0.0))
((0 . "LINE") (100 . "AcDbEntity") (8 . "MASONRY") (62 . 7) (370 . 13) (100 . "AcDbLine") (10 16074.6606334842
339.8940158371 0.0) (11 16266.9683257919 339.8940158371 0.0))
((0 . "LINE") (100 . "AcDbEntity") (8 . "MASONRY") (62 . 7) (370 . 13) (100 . "AcDbLine") (10 16266.9683257919
339.8940158371 0.0) (11 16459.2760180996 339.8940158371 0.0))
((0 . "LINE") (100 . "AcDbEntity") (8 . "MASONRY") (62 . 7) (370 . 13) (100 . "AcDbLine") (10 16459.2760180996
339.8940158371 0.0) (11 16651.5837104072 339.8940158371 0.0))
((0 . "LINE") (100 . "AcDbEntity") (8 . "MASONRY") (62 . 7) (370 . 13) (100 . "AcDbLine") (10 16651.5837104072
339.8940158371 0.0) (11 16843.8914027149 339.8940158371 0.0))
((0 . "LINE") (100 . "AcDbEntity") (8 . "MASONRY") (62 . 7) (370 . 13) (100 . "AcDbLine") (10 16843.8914027149
339.8940158371 0.0) (11 17036.1990950226 339.8940158371 0.0))
((0 . "LINE") (100 . "AcDbEntity") (8 . "MASONRY") (62 . 7) (370 . 13) (100 . "AcDbLine") (10 17036.1990950226
339.8940158371 0.0) (11 17196.3675904977 339.8940158371 0.0))
((0 . "LINE") (100 . "AcDbEntity") (8 . "MASONRY") (62 . 7) (370 . 13) (100 . "AcDbLine") (10 12228.5067873303
339.8940158371 0.0) (11 12228.5067873303 265.3441289593 0.0))
((0 . "LINE") (100 . "AcDbEntity") (8 . "MASONRY") (62 . 7) (370 . 13) (100 . "AcDbLine") (10 12613.1221719457
339.8940158371 0.0) (11 12613.1221719457 265.3441289593 0.0))
((0 . "LINE") (100 . "AcDbEntity") (8 . "MASONRY") (62 . 7) (370 . 13) (100 . "AcDbLine") (10 12997.7375565611
339.8940158371 0.0) (11 12997.7375565611 265.3441289593 0.0))
((0 . "LINE") (100 . "AcDbEntity") (8 . "MASONRY") (62 . 7) (370 . 13) (100 . "AcDbLine") (10 13382.3529411765
339.8940158371 0.0) (11 13382.3529411765 265.3441289593 0.0))
((0 . "LINE") (100 . "AcDbEntity") (8 . "MASONRY") (62 . 7) (370 . 13) (100 . "AcDbLine") (10 13766.9683257919
339.8940158371 0.0) (11 13766.9683257919 265.3441289593 0.0))
((0 . "LINE") (100 . "AcDbEntity") (8 . "MASONRY") (62 . 7) (370 . 13) (100 . "AcDbLine") (10 14151.5837104072
339.8940158371 0.0) (11 14151.5837104072 265.3441289593 0.0))
((0 . "LINE") (100 . "AcDbEntity") (8 . "MASONRY") (62 . 7) (370 . 13) (100 . "AcDbLine") (10 14536.1990950226
339.8940158371 0.0) (11 14536.1990950226 265.3441289593 0.0))
((0 . "LINE") (100 . "AcDbEntity") (8 . "MASONRY") (62 . 7) (370 . 13) (100 . "AcDbLine") (10 14920.814479638
339.8940158371 0.0) (11 14920.814479638 265.3441289593 0.0))
((0 . "LINE") (100 . "AcDbEntity") (8 . "MASONRY") (62 . 7) (370 . 13) (100 . "AcDbLine") (10 15305.4298642534
339.8940158371 0.0) (11 15305.4298642534 265.3441289593 0.0))
((0 . "LINE") (100 . "AcDbEntity") (8 . "MASONRY") (62 . 7) (370 . 13) (100 . "AcDbLine") (10 15690.0452488688
339.8940158371 0.0) (11 15690.0452488688 265.3441289593 0.0))
((0 . "LINE") (100 . "AcDbEntity") (8 . "MASONRY") (62 . 7) (370 . 13) (100 . "AcDbLine") (10 16074.6606334842
339.8940158371 0.0) (11 16074.6606334842 265.3441289593 0.0))
((0 . "LINE") (100 . "AcDbEntity") (8 . "MASONRY") (62 . 7) (370 . 13) (100 . "AcDbLine") (10 16459.2760180996
339.8940158371 0.0) (11 16459.2760180996 265.3441289593 0.0))
((0 . "LINE") (100 . "AcDbEntity") (8 . "MASONRY") (62 . 7) (370 . 13) (100 . "AcDbLine") (10 16843.8914027149
339.8940158371 0.0) (11 16843.8914027149 265.3441289593 0.0))
((0 . "LINE") (100 . "AcDbEntity") (8 . "MASONRY") (62 . 7) (370 . 13) (100 . "AcDbLine") (10 12132.7121832579
265.3441289593 0.0) (11 12228.5067873303 265.3441289593 0.0))
((0 . "LINE") (100 . "AcDbEntity") (8 . "MASONRY") (62 . 7) (370 . 13) (100 . "AcDbLine") (10 12228.5067873303
265.3441289593 0.0) (11 12613.1221719457 265.3441289593 0.0))
((0 . "LINE") (100 . "AcDbEntity") (8 . "MASONRY") (62 . 7) (370 . 13) (100 . "AcDbLine") (10 12613.1221719457
265.3441289593 0.0) (11 12997.7375565611 265.3441289593 0.0))
((0 . "LINE") (100 . "AcDbEntity") (8 . "MASONRY") (62 . 7) (370 . 13) (100 . "AcDbLine") (10 12997.7375565611
265.3441289593 0.0) (11 13382.3529411765 265.3441289593 0.0))
((0 . "LINE") (100 . "AcDbEntity") (8 . "MASONRY") (62 . 7) (370 . 13) (100 . "AcDbLine") (10 13382.3529411765
265.3441289593 0.0) (11 13766.9683257919 265.3441289593 0.0))
((0 . "LINE") (100 . "AcDbEntity") (8 . "MASONRY") (62 . 7) (370 . 13) (100 . "AcDbLine") (10 13766.9683257919
265.3441289593 0.0) (11 14151.5837104072 265.3441289593 0.0))
((0 . "LINE") (100 . "AcDbEntity") (8 . "MASONRY") (62 . 7) (370 . 13) (100 . "AcDbLine") (10 14151.5837104072
265.3441289593 0.0) (11 14536.1990950226 265.3441289593 0.0))
((0 . "LINE") (100 . "AcDbEntity") (8 . "MASONRY") (62 . 7) (370 . 13) (100 . "AcDbLine") (10 14536.1990950226
265.3441289593 0.0) (11 14920.814479638 265.3441289593 0.0))
((0 . "LINE") (100 . "AcDbEntity") (8 . "MASONRY") (62 . 7) (370 . 13) (100 . "AcDbLine") (10 14920.814479638
265.3441289593 0.0) (11 15305.4298642534 265.3441289593 0.0))
((0 . "LINE") (100 . "AcDbEntity") (8 . "MASONRY") (62 . 7) (370 . 13) (100 . "AcDbLine") (10 15305.4298642534
265.3441289593 0.0) (11 15690.0452488688 265.3441289593 0.0))
((0 . "LINE") (100 . "AcDbEntity") (8 . "MASONRY") (62 . 7) (370 . 13) (100 . "AcDbLine") (10 15690.0452488688
265.3441289593 0.0) (11 16074.6606334842 265.3441289593 0.0))
((0 . "LINE") (100 . "AcDbEntity") (8 . "MASONRY") (62 . 7) (370 . 13) (100 . "AcDbLine") (10 16074.6606334842
265.3441289593 0.0) (11 16459.2760180996 265.3441289593 0.0))
((0 . "LINE") (100 . "AcDbEntity") (8 . "MASONRY") (62 . 7) (370 . 13) (100 . "AcDbLine") (10 16459.2760180996
265.3441289593 0.0) (11 16843.8914027149 265.3441289593 0.0))
((0 . "LINE") (100 . "AcDbEntity") (8 . "MASONRY") (62 . 7) (370 . 13) (100 . "AcDbLine") (10 16843.8914027149
265.3441289593 0.0) (11 17208.7925678733 265.3441289593 0.0))
((0 . "ARC") (100 . "AcDbEntity") (8 . "WINDOWS") (62 . 7) (370 . 13) (100 . "AcDbCircle") (10 5441.1764705882
3850.6787330317 0.0) (40 . 1420.814479638) (100 . "AcDbArc") (50 . 0.9986934434) (51 . 2.1428992102))
((0 . "ARC") (100 . "AcDbEntity") (8 . "WINDOWS") (62 . 7) (370 . 13) (100 . "AcDbCircle") (10 5446.8325791855
3611.8966817496 0.0) (40 . 1557.7865761689) (100 . "AcDbArc") (50 . 1.0997063654) (51 . 2.0418862882))
((0 . "ARC") (100 . "AcDbEntity") (8 . "WINDOWS") (62 . 7) (370 . 13) (100 . "AcDbCircle") (10 5446.8325791855
3420.8851809955 0.0) (40 . 1680.9247737557) (100 . "AcDbArc") (50 . 1.16615307) (51 . 1.5472399948))
((0 . "ARC") (100 . "AcDbEntity") (8 . "WINDOWS") (62 . 7) (370 . 13) (100 . "AcDbCircle") (10 5446.8325791855
3420.8851809955 0.0) (40 . 1680.9247737557) (100 . "AcDbArc") (50 . 1.5472399948) (51 . 1.5943526588))
((0 . "ARC") (100 . "AcDbEntity") (8 . "WINDOWS") (62 . 7) (370 . 13) (100 . "AcDbCircle") (10 5446.8325791855
3420.8851809955 0.0) (40 . 1680.9247737557) (100 . "AcDbArc") (50 . 1.5943526588) (51 . 1.9754395836))
((0 . "ARC") (100 . "AcDbEntity") (8 . "WINDOWS") (62 . 7) (370 . 13) (100 . "AcDbCircle") (10 5435.520361991
1213.1763763198 0.0) (40 . 1241.574754902) (100 . "AcDbArc") (50 . 0.896796493) (51 . 2.2447961606))
((0 . "ARC") (100 . "AcDbEntity") (8 . "WINDOWS") (62 . 7) (370 . 13) (100 . "AcDbCircle") (10 5441.1764705882
1139.9886877828 0.0) (40 . 1235.5769230769) (100 . "AcDbArc") (50 . 0.9560013805) (51 . 2.185591273))
((0 . "ARC") (100 . "AcDbEntity") (8 . "WINDOWS") (62 . 7) (370 . 13) (100 . "AcDbCircle") (10 5441.1764705882
1112.0537958773 0.0) (40 . 1195.638511815) (100 . "AcDbArc") (50 . 0.978566035) (51 . 1.5329423463))
((0 . "ARC") (100 . "AcDbEntity") (8 . "WINDOWS") (62 . 7) (370 . 13) (100 . "AcDbCircle") (10 5441.1764705882
1112.0537958773 0.0) (40 . 1195.638511815) (100 . "AcDbArc") (50 . 1.5329423463) (51 . 1.599183845))
((0 . "ARC") (100 . "AcDbEntity") (8 . "WINDOWS") (62 . 7) (370 . 13) (100 . "AcDbCircle") (10 5441.1764705882
1112.0537958773 0.0) (40 . 1195.638511815) (100 . "AcDbArc") (50 . 1.599183845) (51 . 2.1630266185))
((0 . "ARC") (100 . "AcDbEntity") (8 . "WINDOWS") (62 . 7) (370 . 13) (100 . "AcDbCircle") (10 14592.7601809955
3850.6787330317 0.0) (40 . 1420.814479638) (100 . "AcDbArc") (50 . 0.9986934434) (51 . 2.1428992102))
((0 . "ARC") (100 . "AcDbEntity") (8 . "WINDOWS") (62 . 7) (370 . 13) (100 . "AcDbCircle") (10 14598.4162895928
3611.8966817496 0.0) (40 . 1557.7865761689) (100 . "AcDbArc") (50 . 1.0997063654) (51 . 2.0418862882))
((0 . "ARC") (100 . "AcDbEntity") (8 . "WINDOWS") (62 . 7) (370 . 13) (100 . "AcDbCircle") (10 14598.4162895928
3420.8851809955 0.0) (40 . 1680.9247737557) (100 . "AcDbArc") (50 . 1.16615307) (51 . 1.5472399948))
((0 . "ARC") (100 . "AcDbEntity") (8 . "WINDOWS") (62 . 7) (370 . 13) (100 . "AcDbCircle") (10 14598.4162895928
3420.8851809955 0.0) (40 . 1680.9247737557) (100 . "AcDbArc") (50 . 1.5472399948) (51 . 1.5943526588))
((0 . "ARC") (100 . "AcDbEntity") (8 . "WINDOWS") (62 . 7) (370 . 13) (100 . "AcDbCircle") (10 14598.4162895928
3420.8851809955 0.0) (40 . 1680.9247737557) (100 . "AcDbArc") (50 . 1.5943526588) (51 . 1.9754395836))
((0 . "ARC") (100 . "AcDbEntity") (8 . "WINDOWS") (62 . 7) (370 . 13) (100 . "AcDbCircle") (10 14587.1040723982
1213.1763763198 0.0) (40 . 1241.574754902) (100 . "AcDbArc") (50 . 0.896796493) (51 . 2.2447961606))
((0 . "ARC") (100 . "AcDbEntity") (8 . "WINDOWS") (62 . 7) (370 . 13) (100 . "AcDbCircle") (10 14592.7601809955
1139.9886877828 0.0) (40 . 1235.5769230769) (100 . "AcDbArc") (50 . 0.9560013805) (51 . 2.185591273))
((0 . "ARC") (100 . "AcDbEntity") (8 . "WINDOWS") (62 . 7) (370 . 13) (100 . "AcDbCircle") (10 14592.7601809955
1112.0537958773 0.0) (40 . 1195.638511815) (100 . "AcDbArc") (50 . 0.978566035) (51 . 1.5329423463))
((0 . "ARC") (100 . "AcDbEntity") (8 . "WINDOWS") (62 . 7) (370 . 13) (100 . "AcDbCircle") (10 14592.7601809955
1112.0537958773 0.0) (40 . 1195.638511815) (100 . "AcDbArc") (50 . 1.5329423463) (51 . 1.599183845))
((0 . "ARC") (100 . "AcDbEntity") (8 . "WINDOWS") (62 . 7) (370 . 13) (100 . "AcDbCircle") (10 14592.7601809955
1112.0537958773 0.0) (40 . 1195.638511815) (100 . "AcDbArc") (50 . 1.599183845) (51 . 2.1630266185))
((0 . "ARC") (100 . "AcDbEntity") (8 . "WINDOWS") (62 . 7) (370 . 13) (100 . "AcDbCircle") (10 1832.5791855204
4745.2394419306 0.0) (40 . 571.5026395173) (100 . "AcDbArc") (50 . 0.55265455) (51 . 1.451835914))
((0 . "ARC") (100 . "AcDbEntity") (8 . "WINDOWS") (62 . 7) (370 . 13) (100 . "AcDbCircle") (10 1832.5791855204
4745.2394419306 0.0) (40 . 571.5026395173) (100 . "AcDbArc") (50 . 1.6897567396) (51 . 2.5889381036))
((0 . "ARC") (100 . "AcDbEntity") (8 . "WINDOWS") (62 . 7) (370 . 13) (100 . "AcDbCircle") (10 1832.5791855204
4651.9829651318 0.0) (40 . 551.6369443705) (100 . "AcDbArc") (50 . 0.709411304) (51 . 2.4321813496))
((0 . "ARC") (100 . "AcDbEntity") (8 . "WINDOWS") (62 . 7) (370 . 13) (100 . "AcDbCircle") (10 1832.5791855204
4594.0654368256 0.0) (40 . 519.0567351201) (100 . "AcDbArc") (50 . 0.799030988) (51 . 1.5053682643))
((0 . "ARC") (100 . "AcDbEntity") (8 . "WINDOWS") (62 . 7) (370 . 13) (100 . "AcDbCircle") (10 1832.5791855204
4594.0654368256 0.0) (40 . 519.0567351201) (100 . "AcDbArc") (50 . 1.5053682643) (51 . 1.6362243893))
((0 . "ARC") (100 . "AcDbEntity") (8 . "WINDOWS") (62 . 7) (370 . 13) (100 . "AcDbCircle") (10 1832.5791855204
4594.0654368256 0.0) (40 . 519.0567351201) (100 . "AcDbArc") (50 . 1.6362243893) (51 . 2.3425616656))
((0 . "ARC") (100 . "AcDbEntity") (8 . "WINDOWS") (62 . 7) (370 . 13) (100 . "AcDbCircle") (10 1832.5791855204
1917.1851432881 0.0) (40 . 571.5026395173) (100 . "AcDbArc") (50 . 0.55265455) (51 . 1.451835914))
((0 . "ARC") (100 . "AcDbEntity") (8 . "WINDOWS") (62 . 7) (370 . 13) (100 . "AcDbCircle") (10 1832.5791855204
1917.1851432881 0.0) (40 . 571.5026395173) (100 . "AcDbArc") (50 . 1.6897567396) (51 . 2.5889381036))
((0 . "ARC") (100 . "AcDbEntity") (8 . "WINDOWS") (62 . 7) (370 . 13) (100 . "AcDbCircle") (10 1832.5791855204
1823.9286664892 0.0) (40 . 551.6369443705) (100 . "AcDbArc") (50 . 0.709411304) (51 . 2.4321813496))
((0 . "ARC") (100 . "AcDbEntity") (8 . "WINDOWS") (62 . 7) (370 . 13) (100 . "AcDbCircle") (10 1832.5791855204
1766.0111381831 0.0) (40 . 519.0567351201) (100 . "AcDbArc") (50 . 0.799030988) (51 . 1.5053682643))
((0 . "ARC") (100 . "AcDbEntity") (8 . "WINDOWS") (62 . 7) (370 . 13) (100 . "AcDbCircle") (10 1832.5791855204
1766.0111381831 0.0) (40 . 519.0567351201) (100 . "AcDbArc") (50 . 1.5053682643) (51 . 1.6362243893))
((0 . "ARC") (100 . "AcDbEntity") (8 . "WINDOWS") (62 . 7) (370 . 13) (100 . "AcDbCircle") (10 1832.5791855204
1766.0111381831 0.0) (40 . 519.0567351201) (100 . "AcDbArc") (50 . 1.6362243893) (51 . 2.3425616656))
((0 . "ARC") (100 . "AcDbEntity") (8 . "WINDOWS") (62 . 7) (370 . 13) (100 . "AcDbCircle") (10 18167.4208144796
4745.2394419306 0.0) (40 . 571.5026395173) (100 . "AcDbArc") (50 . 0.55265455) (51 . 1.451835914))
((0 . "ARC") (100 . "AcDbEntity") (8 . "WINDOWS") (62 . 7) (370 . 13) (100 . "AcDbCircle") (10 18167.4208144796
4745.2394419306 0.0) (40 . 571.5026395173) (100 . "AcDbArc") (50 . 1.6897567396) (51 . 2.5889381036))
((0 . "ARC") (100 . "AcDbEntity") (8 . "WINDOWS") (62 . 7) (370 . 13) (100 . "AcDbCircle") (10 18167.4208144796
4651.9829651318 0.0) (40 . 551.6369443705) (100 . "AcDbArc") (50 . 0.709411304) (51 . 2.4321813496))
((0 . "ARC") (100 . "AcDbEntity") (8 . "WINDOWS") (62 . 7) (370 . 13) (100 . "AcDbCircle") (10 18167.4208144796
4594.0654368256 0.0) (40 . 519.0567351201) (100 . "AcDbArc") (50 . 0.799030988) (51 . 1.5053682643))
((0 . "ARC") (100 . "AcDbEntity") (8 . "WINDOWS") (62 . 7) (370 . 13) (100 . "AcDbCircle") (10 18167.4208144796
4594.0654368256 0.0) (40 . 519.0567351201) (100 . "AcDbArc") (50 . 1.5053682643) (51 . 1.6362243893))
((0 . "ARC") (100 . "AcDbEntity") (8 . "WINDOWS") (62 . 7) (370 . 13) (100 . "AcDbCircle") (10 18167.4208144796
4594.0654368256 0.0) (40 . 519.0567351201) (100 . "AcDbArc") (50 . 1.6362243893) (51 . 2.3425616656))
((0 . "ARC") (100 . "AcDbEntity") (8 . "WINDOWS") (62 . 7) (370 . 13) (100 . "AcDbCircle") (10 18167.4208144796
1917.1851432881 0.0) (40 . 571.5026395173) (100 . "AcDbArc") (50 . 0.55265455) (51 . 1.451835914))
((0 . "ARC") (100 . "AcDbEntity") (8 . "WINDOWS") (62 . 7) (370 . 13) (100 . "AcDbCircle") (10 18167.4208144796
1917.1851432881 0.0) (40 . 571.5026395173) (100 . "AcDbArc") (50 . 1.6897567396) (51 . 2.5889381036))
((0 . "ARC") (100 . "AcDbEntity") (8 . "WINDOWS") (62 . 7) (370 . 13) (100 . "AcDbCircle") (10 18167.4208144796
1823.9286664892 0.0) (40 . 551.6369443705) (100 . "AcDbArc") (50 . 0.709411304) (51 . 2.4321813496))
((0 . "ARC") (100 . "AcDbEntity") (8 . "WINDOWS") (62 . 7) (370 . 13) (100 . "AcDbCircle") (10 18167.4208144796
1766.0111381831 0.0) (40 . 519.0567351201) (100 . "AcDbArc") (50 . 0.799030988) (51 . 1.5053682643))
((0 . "ARC") (100 . "AcDbEntity") (8 . "WINDOWS") (62 . 7) (370 . 13) (100 . "AcDbCircle") (10 18167.4208144796
1766.0111381831 0.0) (40 . 519.0567351201) (100 . "AcDbArc") (50 . 1.5053682643) (51 . 1.6362243893))
((0 . "ARC") (100 . "AcDbEntity") (8 . "WINDOWS") (62 . 7) (370 . 13) (100 . "AcDbCircle") (10 18167.4208144796
1766.0111381831 0.0) (40 . 519.0567351201) (100 . "AcDbArc") (50 . 1.6362243893) (51 . 2.3425616656))
((0 . "ARC") (100 . "AcDbEntity") (8 . "WINDOWS") (62 . 7) (370 . 13) (100 . "AcDbCircle") (10 8755.6561085973
4758.9627567003 0.0) (40 . 648.2770623042) (100 . "AcDbArc") (50 . 0.57795082) (51 . 2.5636418336))
((0 . "ARC") (100 . "AcDbEntity") (8 . "WINDOWS") (62 . 7) (370 . 13) (100 . "AcDbCircle") (10 8755.6561085973
4666.918049271 0.0) (40 . 604.5751633987) (100 . "AcDbArc") (50 . 0.7250884745) (51 . 2.4165041791))
((0 . "ARC") (100 . "AcDbEntity") (8 . "WINDOWS") (62 . 7) (370 . 13) (100 . "AcDbCircle") (10 8755.6561085973
4687.5831780676 0.0) (40 . 527.3489486292) (100 . "AcDbArc") (50 . 0.688437366) (51 . 1.5063985133))
((0 . "ARC") (100 . "AcDbEntity") (8 . "WINDOWS") (62 . 7) (370 . 13) (100 . "AcDbCircle") (10 8755.6561085973
4687.5831780676 0.0) (40 . 527.3489486292) (100 . "AcDbArc") (50 . 1.5063985133) (51 . 1.6351941403))
((0 . "ARC") (100 . "AcDbEntity") (8 . "WINDOWS") (62 . 7) (370 . 13) (100 . "AcDbCircle") (10 8755.6561085973
4687.5831780676 0.0) (40 . 527.3489486292) (100 . "AcDbArc") (50 . 1.6351941403) (51 . 2.4531552876))
((0 . "ARC") (100 . "AcDbEntity") (8 . "WINDOWS") (62 . 7) (370 . 13) (100 . "AcDbCircle") (10 8755.6561085973
1304.6757164404 0.0) (40 . 1093.5143288084) (100 . "AcDbArc") (50 . 0.7610127542) (51 . 1.5138507949))
((0 . "ARC") (100 . "AcDbEntity") (8 . "WINDOWS") (62 . 7) (370 . 13) (100 . "AcDbCircle") (10 8755.6561085973
1304.6757164404 0.0) (40 . 1093.5143288084) (100 . "AcDbArc") (50 . 1.6277418587) (51 . 2.3805798994))
((0 . "ARC") (100 . "AcDbEntity") (8 . "WINDOWS") (62 . 7) (370 . 13) (100 . "AcDbCircle") (10 8755.6561085973
1268.3257918552 0.0) (40 . 1039.3665158371) (100 . "AcDbArc") (50 . 0.8152630109) (51 . 2.3263296427))
((0 . "ARC") (100 . "AcDbEntity") (8 . "WINDOWS") (62 . 7) (370 . 13) (100 . "AcDbCircle") (10 8755.6561085973
1239.2019744961 0.0) (40 . 989.3048128342) (100 . "AcDbArc") (50 . 0.8457078523) (51 . 1.5250423189))
((0 . "ARC") (100 . "AcDbEntity") (8 . "WINDOWS") (62 . 7) (370 . 13) (100 . "AcDbCircle") (10 8755.6561085973
1239.2019744961 0.0) (40 . 989.3048128342) (100 . "AcDbArc") (50 . 1.5250423189) (51 . 1.6165503347))
((0 . "ARC") (100 . "AcDbEntity") (8 . "WINDOWS") (62 . 7) (370 . 13) (100 . "AcDbCircle") (10 8755.6561085973
1239.2019744961 0.0) (40 . 989.3048128342) (100 . "AcDbArc") (50 . 1.6165503347) (51 . 2.2958848013))
((0 . "ARC") (100 . "AcDbEntity") (8 . "WINDOWS") (62 . 7) (370 . 13) (100 . "AcDbCircle") (10 11255.6561085973
4758.9627567003 0.0) (40 . 648.2770623042) (100 . "AcDbArc") (50 . 0.57795082) (51 . 2.5636418336))
((0 . "ARC") (100 . "AcDbEntity") (8 . "WINDOWS") (62 . 7) (370 . 13) (100 . "AcDbCircle") (10 11255.6561085973
4666.918049271 0.0) (40 . 604.5751633987) (100 . "AcDbArc") (50 . 0.7250884745) (51 . 2.4165041791))
((0 . "ARC") (100 . "AcDbEntity") (8 . "WINDOWS") (62 . 7) (370 . 13) (100 . "AcDbCircle") (10 11255.6561085973
4687.5831780676 0.0) (40 . 527.3489486292) (100 . "AcDbArc") (50 . 0.688437366) (51 . 1.5063985133))
((0 . "ARC") (100 . "AcDbEntity") (8 . "WINDOWS") (62 . 7) (370 . 13) (100 . "AcDbCircle") (10 11255.6561085973
4687.5831780676 0.0) (40 . 527.3489486292) (100 . "AcDbArc") (50 . 1.5063985133) (51 . 1.6351941403))
((0 . "ARC") (100 . "AcDbEntity") (8 . "WINDOWS") (62 . 7) (370 . 13) (100 . "AcDbCircle") (10 11255.6561085973
4687.5831780676 0.0) (40 . 527.3489486292) (100 . "AcDbArc") (50 . 1.6351941403) (51 . 2.4531552876))
((0 . "ARC") (100 . "AcDbEntity") (8 . "WINDOWS") (62 . 7) (370 . 13) (100 . "AcDbCircle") (10 11255.6561085973
1304.6757164404 0.0) (40 . 1093.5143288084) (100 . "AcDbArc") (50 . 0.7610127542) (51 . 0.7758969971))
((0 . "ARC") (100 . "AcDbEntity") (8 . "WINDOWS") (62 . 7) (370 . 13) (100 . "AcDbCircle") (10 11255.6561085973
1304.6757164404 0.0) (40 . 1093.5143288084) (100 . "AcDbArc") (50 . 0.7758969971) (51 . 1.5138507949))
((0 . "ARC") (100 . "AcDbEntity") (8 . "WINDOWS") (62 . 7) (370 . 13) (100 . "AcDbCircle") (10 11255.6561085973
1304.6757164404 0.0) (40 . 1093.5143288084) (100 . "AcDbArc") (50 . 1.6277418587) (51 . 2.3805798994))
((0 . "ARC") (100 . "AcDbEntity") (8 . "WINDOWS") (62 . 7) (370 . 13) (100 . "AcDbCircle") (10 11255.6561085973
1268.3257918552 0.0) (40 . 1039.3665158371) (100 . "AcDbArc") (50 . 0.8152630109) (51 . 2.3263296427))
((0 . "ARC") (100 . "AcDbEntity") (8 . "WINDOWS") (62 . 7) (370 . 13) (100 . "AcDbCircle") (10 11255.6561085973
1239.2019744961 0.0) (40 . 989.3048128342) (100 . "AcDbArc") (50 . 0.8457078523) (51 . 1.5250423189))
((0 . "ARC") (100 . "AcDbEntity") (8 . "WINDOWS") (62 . 7) (370 . 13) (100 . "AcDbCircle") (10 11255.6561085973
1239.2019744961 0.0) (40 . 989.3048128342) (100 . "AcDbArc") (50 . 1.5250423189) (51 . 1.6165503347))
((0 . "ARC") (100 . "AcDbEntity") (8 . "WINDOWS") (62 . 7) (370 . 13) (100 . "AcDbCircle") (10 11255.6561085973
1239.2019744961 0.0) (40 . 989.3048128342) (100 . "AcDbArc") (50 . 1.6165503347) (51 . 2.2958848013))
))
(setq FNP:LAYERS '("ARCH" "GLASS" "GROUND" "LOUVERS" "MASONRY" "SOLAR" "WINDOWS"))
(setq FNP:BLOCK "FACADE_NOPLANTS_F766C3EC49")

(defun FNP:BUILD (name / row)
  (entmake (list '(0 . "BLOCK") '(100 . "AcDbEntity") '(8 . "0")
    '(100 . "AcDbBlockBegin") (cons 2 name) '(70 . 0)
    '(10 0.0 0.0 0.0) (cons 3 name) '(1 . "")))
  (foreach row FNP:DATA (entmake row))
  (entmake '((0 . "ENDBLK") (100 . "AcDbEntity") (8 . "0")
    (100 . "AcDbBlockEnd"))))
(defun c:FACADE_NOPLANTS (/ point width factor name)
  (setq point (getpoint "\nInsertion point: "))
  (if point
    (progn
      (initget 6)
      (setq width (getreal "\nEstimated baseline width in millimetres <20000>: "))
      (if (null width) (setq width 20000.0))
      (setq factor (/ width 20000.0))
      (foreach name FNP:LAYERS
        (if (null (tblsearch "LAYER" name))
          (entmake (list '(0 . "LAYER") '(100 . "AcDbSymbolTableRecord")
            '(100 . "AcDbLayerTableRecord") (cons 2 name) '(70 . 0)
            (cons 62 (if (= name "PLANTS") 94 7)) '(6 . "Continuous") '(370 . 13)))))
      (if (null (tblsearch "BLOCK" FNP:BLOCK)) (FNP:BUILD FNP:BLOCK))
      (entmake (list '(0 . "INSERT") '(100 . "AcDbEntity") '(8 . "0")
        '(100 . "AcDbBlockReference") (cons 2 FNP:BLOCK)
        (cons 10 (trans point 1 0)) (cons 41 factor) (cons 42 factor)
        (cons 43 factor) '(50 . 0.0)))
      (princ "\nInserted geometric facade. EXPLODE for individual entities.")))
  (princ))
(princ "\nLoaded. Run FACADE_NOPLANTS.")
(princ)
