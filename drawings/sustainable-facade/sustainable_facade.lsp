; Source-driven sustainable facade. Units: estimated millimetres.
; Load with APPLOAD, run SUSTAIN. Geometry is embedded; no external files.
; Not a native AutoCAD runtime certification. No 100-percent fidelity claim.
(setq SF:DATA '(
("SF_ARCHITECTURE" 0 ((11.31222 0.00000) (614.63043 -3.77070)))
("SF_ARCHITECTURE" 0 ((509.04977 5818.25045) (516.59785 5811.90633) (2737.55656 5814.48620) (2748.86878 5818.25045)))
("SF_ARCHITECTURE" 0 ((509.04977 5818.25045) (441.32466 5802.11109) (434.69129 5791.85520) (433.78971 5773.00158)
(437.56041 5765.60803) (448.71799 5758.97489) (467.57161 5756.86222) (497.73756 5743.88529) (512.82048 5742.83552)))
("SF_ARCHITECTURE" 0 ((509.04977 5818.25045) (520.36855 5832.27715) (542.98643 5843.59593) (633.48416 5877.52602)
(652.33790 5878.58213)))
("SF_ARCHITECTURE" 0 ((569.38156 5686.27443) (558.06923 5687.47229) (527.90362 5708.89921) (517.79548 5720.21109)
(512.82048 5742.83552)))
("SF_ARCHITECTURE" 0 ((2790.34717 5746.60633) (542.98643 5746.60633) (512.82048 5742.83552)))
("SF_ARCHITECTURE" 0 ((652.33790 5607.08857) (644.78982 5610.71165) (592.00600 5611.01437) (584.47115 5614.78484)
(577.07783 5625.94276) (576.77500 5656.10860) (569.38156 5686.27443)))
("SF_ARCHITECTURE" 0 ((2741.32704 5686.27443) (2726.24434 5690.03869) (746.60633 5690.05181) (723.98190 5693.81606)
(580.69389 5689.89717) (569.38156 5686.27443)))
("SF_ARCHITECTURE" 0 ((2801.65939 -3.77070) (2782.80543 -3.77070) (1251.88529 -3.77070) (1229.26086 -3.77070)
(1025.64095 -3.77070) (980.39208 -3.77070) (961.53846 -3.77070) (614.63043 -3.77070)))
("SF_ARCHITECTURE" 0 ((652.33790 184.76527) (633.48428 179.79061) (622.32670 165.91346) (618.25317 15.08201) (614.63043
-3.77070)))
("SF_ARCHITECTURE" 0 ((648.56708 2809.20034) (652.33790 2737.55656) (652.33790 2058.82353) (648.56708 2032.42862)
(648.56708 592.00509) (652.33133 573.15328) (652.33778 279.03563) (648.56719 230.01414) (652.33790 184.76527)))
("SF_ARCHITECTURE" 0 ((648.56708 2809.20034) (622.17851 2812.07681) (611.00792 2828.05430) (610.86629 2990.19581)
(618.54932 3007.84559) (656.10860 3012.82025)))
("SF_ARCHITECTURE" 0 ((2794.11765 2812.97161) (1953.24310 2816.74208) (1938.15962 2816.74208) (1923.07692 2816.74208)
(1621.41776 2816.74208) (1598.79333 2816.74208) (1210.40724 2816.74208) (1191.55362 2816.74208) (840.87489 2816.73586)
(822.02104 2812.97783) (659.87941 2812.82387) (648.56708 2809.20034)))
("SF_ARCHITECTURE" 0 ((2763.95147 6481.90045) (2745.09830 6478.12964) (2707.39038 6481.89389) (1907.99423 6481.74581)
(1896.83643 6474.35249) (1893.06561 6466.81742) (1892.75633 6346.15385) (1888.98541 6338.76719) (1877.82805 6334.84819)
(1632.72998 6334.84819) (1617.65362 6339.66889) (1610.26018 6349.92466) (1609.95090 6470.58824) (1598.79333 6478.12975)
(674.96233 6478.12975) (652.33790 6478.12975)))
("SF_ARCHITECTURE" 0 ((652.33790 6478.12975) (652.34446 6180.24140) (656.10860 6153.84615) (656.10204 5893.66516)
(652.33790 5878.58213)))
("SF_ARCHITECTURE" 0 ((652.33790 6478.12975) (633.49072 6478.12975) (626.09740 6493.21267) (624.42590 6545.99638)
(633.48439 6557.31527) (1666.66663 6557.31527) (1677.82421 6542.23201) (1679.18314 6399.09876) (1685.52692 6395.32828)
(1787.33032 6395.16697) (1817.49627 6391.40928) (1828.65385 6395.32828) (1832.42455 6402.71493) (1832.72726 6519.60758)
(1837.55419 6542.23201) (1851.43292 6553.38982) (2714.93213 6553.55079) (2763.95147 6557.31550)))
("SF_ARCHITECTURE" 0 ((2797.88835 6195.32421) (1429.11018 6195.33077) (1398.94412 6198.94695) (1304.67579 6160.33767)
(682.50373 5868.32624) (660.02749 5868.47398) (652.33790 5878.58213)))
("SF_ARCHITECTURE" 0 ((652.33790 5607.08857) (656.10204 4841.62896) (652.34446 4822.77568) (652.33133 4483.40916)
(648.57376 4460.78473) (656.10860 4392.91143) (656.10860 3834.84163) (656.10860 3778.28054)))
("SF_ARCHITECTURE" 0 ((652.33790 5607.08857) (667.42081 5610.85351) (2790.34717 5607.08903)))
("SF_ARCHITECTURE" 0 ((2801.65939 180.99548) (667.42081 181.00170) (652.33790 184.76527)))
("SF_PLANTING" 0 ((678.73303 3774.50939) (656.10860 3778.28054)))
("SF_PLANTING" 0 ((656.10860 3778.28054) (656.10860 3766.96833) (656.10860 3736.80283) (656.10860 3650.07500) (656.10860
3619.90950) (656.10860 3533.18224) (656.10860 3506.78733) (656.10860 3457.76799) (656.10860 3408.74785) (656.10860
3058.06912) (656.10860 3012.82025)))
("SF_PLANTING" 0 ((957.76765 3009.04977) (671.19152 3009.05600) (656.10860 3012.82025)))
("SF_PLANTING" 0 ((674.96233 2967.57138) (663.80464 2966.36731) (660.03405 2960.02353) (663.79819 2869.53891) (667.42081
2861.99095)))
("SF_PLANTING" 0 ((697.58676 3766.96833) (705.27636 3755.80419) (750.37715 3722.78235) (757.91855 3722.93020) (773.00158
3735.60464) (791.85520 3740.57274)))
("SF_ARCHITECTURE" 0 ((969.07986 2055.05305) (950.22624 2058.82353) (720.21109 2058.81731) (701.35747 2055.05305)))
("SF_ARCHITECTURE" 0 ((969.07986 2021.11618) (720.21109 2021.11618) (701.35747 2021.11618)))
("SF_PLANTING" 0 ((780.54299 931.37161) (772.99491 934.99581) (742.83552 935.29129) (701.35747 946.45645)))
("SF_PLANTING" 0 ((705.12817 3834.84163) (712.66968 3838.61278)))
("SF_ARCHITECTURE" 0 ((705.12817 1659.12613) (716.44050 1662.88348) (735.29412 1659.13100) (904.97738 1659.12613)
(927.60181 1662.88903) (969.07986 1659.12613)))
("SF_ARCHITECTURE" 0 ((969.07986 4837.85781) (708.89898 4837.85781)))
("SF_ARCHITECTURE" 0 ((969.07986 4803.92115) (953.99706 4800.15124) (720.21120 4803.91493) (708.89898 4800.15124)))
("SF_ARCHITECTURE" 0 ((969.07986 4475.86686) (708.89898 4475.86686)))
("SF_ARCHITECTURE" 0 ((969.07986 4441.93020) (708.89898 4441.93020)))
("SF_PLANTING" 0 ((708.89898 3423.83133) (720.21120 3431.21765) (757.91855 3427.60181)))
("SF_ARCHITECTURE" 0 ((2745.09830 2756.41029) (1621.41776 2756.40430) (1598.79333 2752.63925) (1572.39819 2756.41052)
(1229.26086 2756.40430) (1206.63643 2752.63925) (1184.01199 2756.40430) (1123.68032 2752.63925) (976.62149 2752.64548)
(957.76765 2756.40362) (916.28959 2752.64548) (901.20656 2756.26278) (837.10407 2756.40430) (818.25045 2752.64548)
(795.62602 2756.11425) (784.31380 2752.78699) (720.21120 2752.64548) (708.89898 2756.41052)))
("SF_ARCHITECTURE" 0 ((961.53846 1628.95928) (946.45543 1625.18948) (844.64548 1625.19434) (829.56267 1628.66312)
(814.47964 1625.19434) (720.21120 1625.19434) (708.89898 1628.95928)))
("SF_PLANTING" 0 ((712.66968 1018.09955) (708.89898 1010.55713)))
("SF_PLANTING" 0 ((818.25045 595.77771) (795.62602 607.08235) (731.52330 606.94152) (712.66968 599.54751)))
("SF_PLANTING" 0 ((799.39661 1044.49378) (776.77873 1039.66765) (765.45995 1025.64197)))
("SF_ARCHITECTURE" 0 ((844.64548 5663.65000) (769.23077 5663.65000)))
("SF_PLANTING" 0 ((773.00158 3861.23722) (784.31380 3871.35158) (803.16742 3876.31934)))
("SF_PLANTING" 0 ((776.77217 3503.01686) (799.39005 3520.67217) (806.93824 3521.87002)))
("SF_PLANTING" 0 ((844.64548 3612.36776) (833.33326 3615.84276) (818.25045 3612.37398) (788.09106 3614.93416) (781.74072
3608.59038) (777.07489 3593.52081) (784.31380 3585.97285)))
("SF_PLANTING" 0 ((803.16742 3740.57274) (791.85520 3740.57274)))
("SF_PLANTING" 0 ((803.16742 3766.96833) (796.82353 3759.42036) (791.85520 3740.57274)))
("SF_PLANTING" 0 ((822.02104 3453.99672) (810.86346 3427.60181) (809.65260 3404.97738) (803.02590 3393.81980) (795.62602
3389.89468)))
("SF_PLANTING" 0 ((799.39661 3695.32387) (810.70882 3714.17839)))
("SF_PLANTING" 0 ((871.04072 1044.49378) (837.10407 1036.95419) (818.25045 1037.10124) (799.39661 1044.49378)))
("SF_PLANTING" 0 ((852.18710 1082.20305) (837.10407 1077.38167) (807.08631 1058.52149) (799.39661 1044.49378)))
("SF_PLANTING" 0 ((871.04072 3849.92500) (855.95769 3863.80328) (814.47975 3868.93292) (803.16742 3876.31934)))
("SF_PLANTING" 0 ((803.16742 3876.31934) (810.85701 3890.34604) (825.79186 3895.17387)))
("SF_PLANTING" 0 ((803.16742 3766.96833) (806.93824 3763.19717) (818.25045 3763.19717)))
("SF_PLANTING" 0 ((803.16742 3766.96833) (808.12941 3782.05170) (833.48145 3823.38133) (855.95769 3835.89830) (871.04072
3849.92500)))
("SF_PLANTING" 0 ((810.70882 3725.49061) (804.36516 3729.41550) (803.16742 3740.57274)))
("SF_PLANTING" 0 ((818.25045 3763.19717) (803.16742 3740.57274)))
("SF_PLANTING" 0 ((806.93824 3521.87002) (844.63891 3519.30373) (850.98937 3525.64751) (855.95769 3540.72398)))
("SF_PLANTING" 0 ((806.93824 3521.87002) (819.30011 3551.88846) (840.87489 3563.34842)))
("SF_PLANTING" 0 ((810.70882 3725.49061) (810.70882 3714.17839)))
("SF_PLANTING" 0 ((840.87489 3748.11505) (833.18518 3734.23586) (810.70882 3725.49061)))
("SF_PLANTING" 0 ((874.81154 3710.40724) (822.02115 3706.79106) (810.70882 3714.17839)))
("SF_PLANTING" 0 ((837.10407 3978.12930) (814.47964 3974.35939)))
("SF_PLANTING" 0 ((814.47964 3646.30509) (833.33326 3668.92952)))
("SF_PLANTING" 0 ((822.02104 3453.99672) (814.47964 3472.85068)))
("SF_PLANTING" 0 ((822.02104 3310.70916) (814.47964 3325.79186)))
("SF_PLANTING" 0 ((822.02104 3310.70916) (818.09570 3303.30894) (806.93824 3296.68213) (795.63269 3295.78032) (789.43688
3299.55158) (795.78054 3318.10238) (814.47964 3325.79186)))
("SF_PLANTING" 0 ((878.58213 3367.27025) (855.95769 3362.29491) (825.79197 3343.44785) (815.68394 3333.33982) (814.47964
3325.79186)))
("SF_PLANTING" 0 ((818.25045 3763.19717) (829.56267 3763.19717)))
("SF_PLANTING" 0 ((822.02104 3453.99672) (859.72851 3465.16120) (878.58213 3461.53846)))
("SF_PLANTING" 0 ((848.41629 3314.47964) (822.02104 3310.70916)))
("SF_PLANTING" 0 ((832.39072 3901.77183) (829.56267 3895.17387) (825.79186 3895.17387)))
("SF_PLANTING" 0 ((832.39072 3901.77183) (825.79186 3898.94378) (825.79186 3895.17387)))
("SF_PLANTING" 0 ((840.87489 3748.11505) (829.56267 3763.19717)))
("SF_PLANTING" 0 ((886.12376 3831.07048) (852.33507 3800.90498) (834.38959 3778.28054) (829.56267 3763.19717)))
("SF_PLANTING" 0 ((832.39072 3901.77183) (844.46719 3899.20339) (867.26991 3906.33767) (912.51878 3906.48609)))
("SF_PLANTING" 0 ((832.39072 3901.77183) (830.87794 3913.70057) (863.49932 3947.96380)))
("SF_PLANTING" 1 ((832.39072 3901.77183) (833.33326 3906.48609) (837.10407 3902.71493)))
("SF_PLANTING" 0 ((837.10407 3978.12930) (863.49932 3963.04717)))
("SF_PLANTING" 0 ((871.04072 3989.44152) (855.95769 3988.39197) (837.10407 3978.12930)))
("SF_PLANTING" 0 ((840.87489 3748.11505) (867.26991 3751.88495)))
("SF_PLANTING" 0 ((840.87489 3563.34842) (855.95769 3540.72398)))
("SF_PLANTING" 0 ((840.87489 3563.34842) (844.64548 3612.36776)))
("SF_PLANTING" 0 ((840.87489 916.28959) (855.95769 930.17443) (874.81154 935.14423)))
("SF_PLANTING" 0 ((844.64548 3612.36776) (859.72851 3612.36776)))
("SF_PLANTING" 0 ((848.41629 3333.33360) (848.41629 3314.47964)))
("SF_PLANTING" 0 ((874.81154 3310.70916) (848.41629 3314.47964)))
("SF_PLANTING" 0 ((874.81154 3310.70916) (869.83643 3273.00814) (848.41629 3257.91855)))
("SF_PLANTING" 0 ((852.18710 1082.20305) (871.04072 1082.20305)))
("SF_PLANTING" 0 ((852.18710 1082.20305) (853.39140 1104.82749) (863.49276 1114.93484) (871.04072 1116.13971)))
("SF_PLANTING" 0 ((889.89434 3544.49446) (882.34638 3540.87172) (855.95769 3540.72398)))
("SF_PLANTING" 0 ((889.89434 3608.59729) (859.72851 3612.36776)))
("SF_PLANTING" 0 ((874.81154 3710.40724) (878.43405 3684.01165) (864.55543 3642.53394) (859.72851 3612.36776)))
("SF_PLANTING" 0 ((859.72851 1180.24038) (871.04072 1180.24038)))
("SF_PLANTING" 0 ((863.49932 3947.96380) (863.49932 3963.04717)))
("SF_PLANTING" 0 ((871.04072 3974.35939) (863.49932 3963.04717)))
("SF_PLANTING" 0 ((912.51878 3932.88043) (893.66516 3942.99536) (863.49932 3947.96380)))
("SF_PLANTING" 0 ((863.49932 972.85068) (908.74819 1040.72398)))
("SF_PLANTING" 0 ((863.49932 893.66516) (901.20656 922.62715) (953.99706 927.60181)))
("SF_PLANTING" 0 ((886.12376 3733.03167) (878.57557 3744.33767) (867.26991 3751.88495)))
("SF_PLANTING" 0 ((867.26991 3751.88495) (883.55701 3812.21097) (893.66516 3819.75826)))
("SF_PLANTING" 0 ((908.74819 886.12274) (888.83824 852.18609) (867.26991 829.56165)))
("SF_PLANTING" 0 ((871.04072 3989.44152) (871.04072 3974.35939)))
("SF_PLANTING" 0 ((871.04072 3989.44152) (874.81154 4000.75373)))
("SF_PLANTING" 0 ((889.89434 3978.12930) (871.04072 3974.35939)))
("SF_PLANTING" 0 ((871.04072 3849.92500) (886.12376 3849.92500)))
("SF_PLANTING" 0 ((946.45543 1116.13971) (934.98869 1142.38552) (923.83100 1149.01923) (897.43597 1150.22410) (886.12376
1154.90249) (875.86776 1165.15837) (871.04072 1180.24038)))
("SF_PLANTING" 0 ((984.16290 1161.38857) (965.30928 1166.36324) (938.91403 1186.42952) (920.06041 1184.01923) (882.35305
1187.62817) (871.04072 1180.24038)))
("SF_PLANTING" 0 ((871.04072 1044.49378) (871.04072 1082.20305)))
("SF_PLANTING" 0 ((871.04072 1082.20305) (897.43597 1087.02919) (919.61606 1111.61448) (946.45543 1116.13971)))
("SF_PLANTING" 0 ((871.04072 1044.49378) (901.20000 1044.34672) (908.74819 1040.72398)))
("SF_PLANTING" 0 ((882.35294 731.52432) (871.04072 720.21210)))
("SF_PLANTING" 0 ((920.06041 4046.00260) (874.81154 4049.77376)))
("SF_PLANTING" 0 ((874.81154 3710.40724) (886.12376 3733.03167)))
("SF_PLANTING" 0 ((874.81154 3310.70916) (893.66516 3318.25011)))
("SF_PLANTING" 0 ((927.60181 607.08993) (902.26290 588.23529) (883.26109 558.06844) (874.81154 531.67421)))
("SF_PLANTING" 0 ((878.58213 3461.53846) (878.58213 3435.14355)))
("SF_PLANTING" 0 ((908.74819 3480.39242) (878.58213 3461.53846)))
("SF_PLANTING" 0 ((893.66516 3427.60181) (878.58213 3435.14355)))
("SF_PLANTING" 0 ((878.58213 3435.14355) (863.50588 3423.83133) (856.11900 3412.51912) (859.88303 3401.20690) (878.58213
3382.35294)))
("SF_PLANTING" 0 ((878.58213 3367.27025) (878.58213 3382.35294)))
("SF_PLANTING" 0 ((916.28959 3386.12342) (878.58213 3382.35294)))
("SF_PLANTING" 0 ((893.66516 3352.18676) (878.58213 3367.27025)))
("SF_PLANTING" 0 ((882.35294 731.52432) (893.66516 723.98190)))
("SF_PLANTING" 0 ((882.35294 731.52432) (893.81324 754.00034) (912.51878 768.17443) (950.22624 780.54299)))
("SF_PLANTING" 0 ((882.35294 629.71437) (901.20656 651.14016) (942.68484 659.87839)))
("SF_PLANTING" 0 ((886.12376 3849.92500) (886.12376 3831.07048)))
("SF_PLANTING" 0 ((920.06041 3861.23722) (901.20656 3860.18054) (886.12376 3849.92500)))
("SF_PLANTING" 0 ((886.12376 3831.07048) (893.66516 3827.30057) (893.66516 3819.75826)))
("SF_PLANTING" 0 ((886.12376 3733.03167) (904.97738 3733.03167)))
("SF_PLANTING" 0 ((889.89434 3544.49446) (893.66516 3563.34842) (889.89434 3608.59729)))
("SF_PLANTING" 0 ((889.89434 3608.59729) (901.05192 3619.90950) (901.35464 3646.30509) (912.37070 3710.40724) (911.46267
3721.71946) (904.97738 3733.03167)))
("SF_PLANTING" 0 ((889.89434 3544.49446) (908.74819 3480.39242)))
("SF_PLANTING" 0 ((961.53846 3993.21267) (957.61301 4004.51867) (942.68484 4014.78043) (893.66516 4012.06595)))
("SF_PLANTING" 0 ((893.66516 3819.75826) (904.97749 3809.64389) (919.90566 3803.62568) (923.83100 3797.13382)))
("SF_PLANTING" 0 ((893.66516 3352.18676) (893.66516 3318.25011)))
("SF_PLANTING" 0 ((893.66516 3352.18676) (916.28959 3378.58247)))
("SF_PLANTING" 0 ((927.60181 3306.93790) (893.66516 3318.25011)))
("SF_PLANTING" 0 ((897.43597 946.45645) (919.00407 972.85068) (931.52715 999.24491) (950.22624 1014.32975)))
("SF_PLANTING" 0 ((897.43597 806.93722) (908.74819 810.70984)))
("SF_PLANTING" 0 ((901.20656 3205.12794) (927.74977 3239.06459) (942.68484 3250.37681)))
("SF_PLANTING" 0 ((904.97738 3733.03167) (915.23326 3751.88495) (923.83100 3797.13382)))
("SF_PLANTING" 0 ((904.97738 3114.63020) (916.28959 3122.17195)))
("SF_PLANTING" 0 ((908.74819 3480.39242) (931.37262 3480.39242)))
("SF_PLANTING" 0 ((942.68484 1044.49378) (908.74819 1040.72398)))
("SF_PLANTING" 0 ((935.14321 720.21210) (908.74819 720.21210)))
("SF_PLANTING" 0 ((912.51878 3932.88043) (912.51878 3906.48609)))
("SF_PLANTING" 0 ((912.51878 3932.88043) (927.60181 3947.59514) (961.53846 3951.73495)))
("SF_PLANTING" 0 ((923.83100 3895.17387) (912.51878 3906.48609)))
("SF_PLANTING" 0 ((923.83100 456.25848) (912.51878 429.86425)))
("SF_PLANTING" 0 ((950.22624 3981.90045) (935.14321 3981.75238) (916.28959 3974.35939)))
("SF_PLANTING" 0 ((916.28959 3386.12342) (916.28959 3378.58247)))
("SF_PLANTING" 0 ((916.28959 3386.12342) (917.49389 3401.20690) (942.68484 3427.60181)))
("SF_PLANTING" 0 ((916.28959 3378.58247) (938.91403 3374.81120)))
("SF_PLANTING" 0 ((923.83100 3122.17195) (916.28959 3122.17195)))
("SF_PLANTING" 0 ((942.68484 3178.73303) (927.74989 3171.04355) (916.43756 3144.79638) (916.28959 3122.17195)))
("SF_PLANTING" 0 ((920.06041 3861.23722) (953.99706 3834.84163)))
("SF_PLANTING" 0 ((920.06041 3861.23722) (920.20837 3887.62534) (923.83100 3895.17387)))
("SF_PLANTING" 0 ((923.83100 3895.17387) (961.53179 3914.18179) (969.07986 3929.11052)))
("SF_PLANTING" 0 ((938.91403 3797.13382) (923.83100 3797.13382)))
("SF_PLANTING" 0 ((927.60181 3306.93790) (928.65814 3291.85520) (937.71629 3276.77251) (942.68484 3250.37681)))
("SF_PLANTING" 0 ((946.45543 3322.02138) (927.60181 3306.93790)))
("SF_PLANTING" 0 ((927.60181 607.08993) (953.99706 599.54751)))
("SF_PLANTING" 0 ((927.60181 607.08993) (934.24819 633.48416) (946.45543 644.79638)))
("SF_PLANTING" 0 ((942.68484 3427.60181) (931.37262 3480.39242)))
("SF_PLANTING" 0 ((957.76765 3514.32907) (931.37262 3480.39242)))
("SF_PLANTING" 0 ((950.22624 833.33428) (931.37262 829.56165)))
("SF_PLANTING" 0 ((1014.32873 1289.59276) (991.70430 1290.79072) (961.53846 1304.52771) (935.14321 1300.90498)))
("SF_PLANTING" 0 ((935.14321 720.21210) (935.14321 716.43948) (946.45543 708.89989)))
("SF_PLANTING" 0 ((953.99706 761.68835) (943.73450 750.37613) (935.14321 720.21210)))
("SF_PLANTING" 0 ((957.76765 3680.24174) (954.14502 3699.09502) (953.84231 3778.28054) (938.91403 3797.13382)))
("SF_PLANTING" 0 ((953.99706 3815.98835) (947.49853 3812.06256) (938.91403 3797.13382)))
("SF_PLANTING" 0 ((946.45543 3322.02138) (938.91403 3374.81120)))
("SF_PLANTING" 0 ((961.53846 3382.35294) (938.91403 3374.81120)))
("SF_PLANTING" 0 ((957.76765 1217.94966) (936.49570 1236.80147) (938.91403 1248.11369)))
("SF_PLANTING" 0 ((938.91403 501.50735) (946.46210 511.62240) (961.53846 516.59219)))
("SF_PLANTING" 0 ((961.53846 3382.35294) (956.71799 3412.51912) (950.08473 3423.67670) (942.68484 3427.60181)))
("SF_PLANTING" 0 ((942.68484 3250.37681) (953.84231 3239.06459) (953.99706 3201.35747)))
("SF_PLANTING" 0 ((942.68484 3178.73303) (953.84231 3163.65034) (957.61957 3092.00577) (950.22624 3061.84038)))
("SF_PLANTING" 0 ((942.68484 3178.73303) (945.56052 3193.80950) (953.99706 3201.35747)))
("SF_PLANTING" 0 ((942.68484 1044.49378) (950.22624 1033.18156)))
("SF_PLANTING" 0 ((942.68484 1044.49378) (968.02364 1093.51527) (969.07986 1112.36708)))
("SF_PLANTING" 0 ((946.45543 656.10860) (942.68484 659.87839)))
("SF_PLANTING" 0 ((946.45543 656.10860) (942.68484 656.10860) (942.68484 659.87839)))
("SF_PLANTING" 0 ((942.68484 659.87839) (946.45543 708.89989)))
("SF_PLANTING" 0 ((953.99706 358.22115) (942.68484 358.22115)))
("SF_PLANTING" 0 ((946.45543 3322.02138) (961.39050 3314.33122) (986.73597 3280.54299) (995.62319 3261.68903)
(1035.74898 3216.44016) (1036.95317 3182.50351)))
("SF_PLANTING" 0 ((969.07986 1112.36708) (946.45543 1116.13971)))
("SF_PLANTING" 0 ((984.16290 708.89989) (946.45543 708.89989)))
("SF_PLANTING" 0 ((946.45543 656.10860) (976.62138 654.90373) (1003.01652 625.94174)))
("SF_PLANTING" 0 ((946.45543 656.10860) (946.45543 644.79638)))
("SF_PLANTING" 0 ((953.99706 599.54751) (956.57002 607.09480) (953.84242 633.48416) (946.45543 644.79638)))
("SF_PLANTING" 0 ((950.22624 3981.90045) (961.53846 3951.73495)))
("SF_PLANTING" 0 ((950.22624 3981.90045) (957.76765 3993.21267) (961.53846 3993.21267)))
("SF_PLANTING" 0 ((950.22624 3061.84038) (972.85068 3054.29864)))
("SF_PLANTING" 0 ((957.76765 3009.04977) (950.22624 3061.84038)))
("SF_PLANTING" 0 ((950.22624 2929.86425) (965.30916 2919.76312) (975.42376 2926.24152) (984.16290 2941.17647)))
("SF_PLANTING" 0 ((950.22624 1033.18156) (950.22624 1014.32975)))
("SF_PLANTING" 0 ((1036.95317 1070.89084) (1006.78733 1062.15045) (984.16290 1047.37014) (950.22624 1033.18156)))
("SF_PLANTING" 0 ((965.30928 972.85068) (960.33428 1003.01753) (950.22624 1014.32975)))
("SF_PLANTING" 0 ((950.22624 833.33428) (950.22624 780.54299)))
("SF_PLANTING" 0 ((950.22624 833.33428) (953.99706 927.60181)))
("SF_PLANTING" 0 ((953.99706 761.68835) (950.22624 780.54299)))
("SF_PLANTING" 0 ((953.99706 3834.84163) (953.99706 3815.98835)))
("SF_PLANTING" 0 ((953.99706 3834.84163) (995.47511 3879.03382) (1018.09955 3890.34604) (1033.18258 3891.40271)))
("SF_PLANTING" 0 ((953.99706 3815.98835) (961.54514 3812.36527) (991.70430 3812.21719)))
("SF_PLANTING" 0 ((1010.55814 3144.79638) (991.85249 3160.02760) (972.70271 3190.03903) (953.99706 3201.35747)))
("SF_PLANTING" 0 ((965.30928 972.85068) (964.25305 957.76867) (953.99706 927.60181)))
("SF_PLANTING" 0 ((953.99706 761.68835) (971.79434 746.60011) (984.16290 708.89989)))
("SF_PLANTING" 0 ((953.99706 599.54751) (964.11154 580.69287) (966.50690 565.76550) (972.85068 561.84106)))
("SF_PLANTING" 0 ((953.99706 316.74208) (965.15452 335.59672) (953.99706 358.22115)))
("SF_PLANTING" 0 ((953.99706 358.22115) (961.68654 368.33473) (976.62149 369.53337)))
("SF_PLANTING" 0 ((957.76765 3680.24174) (975.41719 3672.54548) (984.31753 3631.22794) (1021.87036 3612.36776)))
("SF_PLANTING" 0 ((957.76765 3680.24174) (954.14502 3672.69321) (950.22624 3612.36776) (950.37421 3536.95351) (957.76765
3514.32907)))
("SF_PLANTING" 0 ((984.16290 3578.43111) (980.68824 3570.88326) (984.01493 3559.57794) (983.10656 3529.41176) (976.47330
3519.15588) (957.76765 3514.32907)))
("SF_PLANTING" 0 ((957.76765 3009.04977) (957.92229 2986.42534) (965.30928 2975.11312)))
("SF_PLANTING" 0 ((957.76765 3009.04977) (1003.01652 3009.19751) (1018.09955 3012.81403) (1583.71041 3016.59129)
(1602.56414 3009.05600) (1719.45701 3009.04977) (1742.08145 3016.59129) (2797.88812 3012.82025)))
("SF_PLANTING" 0 ((957.76765 1217.94966) (972.68948 1244.34389) (968.92534 1255.50147) (957.76765 1259.42590)))
("SF_PLANTING" 0 ((957.76765 1217.94966) (961.69310 1207.84084) (980.39208 1199.09502)))
("SF_PLANTING" 0 ((961.53846 3993.21267) (987.93371 3985.81946) (1018.09955 3985.67161)))
("SF_PLANTING" 0 ((969.07986 3929.11052) (961.53846 3951.73495)))
("SF_PLANTING" 0 ((961.53846 3382.35294) (972.85079 3381.14876) (999.24593 3355.95803)))
("SF_PLANTING" 0 ((972.85068 411.00962) (959.87364 456.25848) (969.06674 493.96776) (961.53846 516.59219)))
("SF_PLANTING" 0 ((961.53846 516.59219) (970.27115 546.60294) (976.62149 550.52885)))
("SF_PLANTING" 0 ((965.30928 972.85068) (995.47511 976.62048)))
("SF_PLANTING" 0 ((1036.95317 3932.88043) (1025.64095 3925.49400) (984.16290 3925.48744) (969.07986 3929.11052)))
("SF_PLANTING" 0 ((969.07986 1112.36708) (987.93371 1112.51550) (1021.87036 1123.67930)))
("SF_PLANTING" 0 ((972.85068 561.84106) (976.62149 558.06844)))
("SF_PLANTING" 0 ((972.85068 561.84106) (972.85068 558.06844) (976.62149 558.06844)))
("SF_PLANTING" 0 ((972.85068 561.84106) (976.62149 565.61086) (980.39208 561.84106) (976.62149 558.06844)))
("SF_PLANTING" 0 ((976.62149 550.52885) (976.62149 558.06844)))
("SF_PLANTING" 0 ((976.62149 550.52885) (994.42534 542.83179) (1021.87036 505.27998)))
("SF_PLANTING" 0 ((1018.09955 701.35747) (984.16290 708.89989)))
("SF_PLANTING" 0 ((1018.09955 3058.06912) (1020.81391 3073.15260) (987.93371 3125.94242)))
("SF_PLANTING" 0 ((1003.01652 3770.73948) (996.53133 3782.05170) (991.70430 3812.21719)))
("SF_PLANTING" 0 ((1018.09955 3842.38269) (1000.44355 3827.15215) (991.70430 3812.21719)))
("SF_PLANTING" 0 ((991.70430 237.55656) (1003.01663 243.89412) (1014.32217 240.27070) (1020.66606 233.77919) (1021.87036
214.93213)))
("SF_PLANTING" 0 ((995.47511 976.62048) (1014.32873 957.76867)))
("SF_PLANTING" 0 ((995.47511 976.62048) (1006.78733 999.24491)))
("SF_PLANTING" 0 ((1010.55814 3355.95803) (999.24593 3355.95803)))
("SF_PLANTING" 0 ((1033.18258 3310.70916) (1021.87025 3311.91324) (1004.07285 3329.56233) (999.24593 3355.95803)))
("SF_PLANTING" 0 ((1003.01652 3770.73948) (1021.87036 3770.73948)))
("SF_PLANTING" 0 ((1003.01652 3770.73948) (995.63631 3740.57342) (1006.78733 3729.26052)))
("SF_PLANTING" 0 ((1021.87036 3435.14355) (1003.01652 3435.14355)))
("SF_PLANTING" 0 ((1003.01652 625.94174) (1018.09955 625.94174)))
("SF_PLANTING" 0 ((1021.87036 592.00509) (1004.22081 599.70215) (999.54197 618.39457) (1003.01652 625.94174)))
("SF_PLANTING" 0 ((1006.78733 3729.26052) (1011.75577 3699.10124) (1018.09955 3691.55396)))
("SF_PLANTING" 0 ((1029.41176 3744.34389) (1006.78733 3729.26052)))
("SF_PLANTING" 0 ((1033.18258 3310.70916) (1036.80520 3318.25701) (1035.74887 3340.71991) (1010.55814 3355.95803)))
("SF_PLANTING" 0 ((1021.87036 3435.14355) (1036.43654 3390.10871) (1022.02500 3378.58247) (1010.55814 3355.95803)))
("SF_PLANTING" 0 ((1014.32873 1289.59276) (1014.47681 1263.19853) (1029.41176 1225.48925)))
("SF_PLANTING" 0 ((1014.32873 1289.59276) (1018.09955 1297.13518) (1021.87036 1297.13518)))
("SF_PLANTING" 0 ((1023.75566 903.09106) (1010.70622 923.83201) (1014.32873 957.76867)))
("SF_PLANTING" 0 ((1048.26538 967.19457) (1014.32873 957.76867)))
("SF_PLANTING" 0 ((1014.32873 282.80543) (1017.95147 301.66007) (1006.94197 429.86425) (1018.09955 452.48869)))
("SF_PLANTING" 0 ((1025.64095 3993.21267) (1018.09955 3993.21267)))
("SF_PLANTING" 0 ((1018.09955 3985.67161) (1018.09955 3993.21267)))
("SF_PLANTING" 0 ((1023.75566 4070.51324) (1003.01652 4077.22477) (969.07986 4105.13722) (950.22624 4108.89468)
(937.39729 4095.02262) (946.60362 4072.39819) (1018.09955 3993.21267)))
("SF_PLANTING" 0 ((1036.95317 3932.88043) (1018.09955 3985.67161)))
("SF_PLANTING" 0 ((1025.64095 3627.45057) (1018.09955 3691.55396)))
("SF_PLANTING" 0 ((1018.09955 3691.55396) (1052.03620 3696.99604) (1082.20204 3687.93088) (1101.05588 3687.78281)))
("SF_PLANTING" 0 ((1025.64095 690.04525) (1018.09955 701.35747)))
("SF_PLANTING" 0 ((1018.09955 701.35747) (1021.87036 742.83654)))
("SF_PLANTING" 0 ((1021.87036 592.00509) (1035.52839 610.85973) (1018.09955 625.94174)))
("SF_PLANTING" 0 ((1025.64095 690.04525) (1025.49299 652.33880) (1018.09955 625.94174)))
("SF_PLANTING" 0 ((1044.49480 426.09446) (1029.26380 447.66176) (1018.09955 452.48869)))
("SF_PLANTING" 0 ((1018.09955 452.48869) (1011.76244 475.11312) (1021.87036 505.27998)))
("SF_PLANTING" 0 ((1029.41176 3744.34389) (1021.87036 3770.73948)))
("SF_PLANTING" 0 ((1055.80701 3785.82161) (1036.95317 3781.00124) (1021.87036 3770.73948)))
("SF_PLANTING" 0 ((1021.87036 3612.36776) (1029.78032 3559.79819) (1043.29038 3551.88778) (1044.49480 3529.41176)))
("SF_PLANTING" 0 ((1021.87036 3612.36776) (1025.64095 3627.45057)))
("SF_PLANTING" 0 ((1021.87036 3435.14355) (1021.87036 3450.22624)))
("SF_PLANTING" 0 ((1021.87036 3450.22624) (1018.24774 3465.30894) (1025.64095 3480.39242)))
("SF_PLANTING" 0 ((1021.87036 3450.22624) (1036.94661 3451.43043) (1044.33348 3461.53846) (1040.56934 3472.70226)
(1025.64095 3480.39242)))
("SF_PLANTING" 0 ((1021.87036 1297.13518) (1055.80701 1297.13518)))
("SF_ARCHITECTURE" 0 ((1067.11923 2352.94118) (1055.80690 2359.42647) (1036.95317 2360.33439) (1021.87025 2355.65532)
(1021.87025 2341.62896) (1021.87025 2307.69231) (1021.87025 1896.68201) (1021.87025 1877.82805) (1021.87025 1772.24830)
(1021.87025 1749.62387) (1021.87025 1677.97794) (1021.87025 1655.35351) (1021.87025 1312.21719) (1021.87036
1297.13518)))
("SF_PLANTING" 0 ((1074.66063 1108.59729) (1021.87036 1123.67930)))
("SF_PLANTING" 0 ((1025.64095 1172.70079) (1022.01833 1161.38857) (1021.87036 1123.67930)))
("SF_PLANTING" 0 ((1023.75566 903.09106) (1015.45249 893.73281) (1010.56471 878.58314) (1010.70611 806.93722)
(1017.95158 780.54299) (1018.24751 750.38371) (1021.87036 742.83654)))
("SF_PLANTING" 0 ((1021.87036 742.83654) (1040.72387 747.80430) (1050.83190 757.91855) (1052.03620 803.16742)))
("SF_PLANTING" 0 ((1021.87036 592.00509) (1026.69729 569.38066) (1058.37986 535.44400) (1063.34842 512.81957)))
("SF_PLANTING" 0 ((1021.87036 505.27998) (1048.26538 505.42771) (1063.34842 512.81957)))
("SF_PLANTING" 0 ((1023.75566 4070.51324) (1055.80701 4068.62704)))
("SF_PLANTING" 0 ((1023.75566 4070.51324) (1025.64095 3993.21267)))
("SF_PLANTING" 0 ((1023.75566 4070.51324) (1025.64095 4128.95928)))
("SF_PLANTING" 0 ((1023.75566 903.09106) (1044.49468 882.50758) (1055.80701 878.58314)))
("SF_PLANTING" 0 ((1048.26538 935.14423) (1023.75566 903.09106)))
("SF_ARCHITECTURE" 0 ((1025.64095 4128.95928) (1025.64106 4170.43699) (1025.64106 4313.72590) (1025.64106 4336.35034)
(1025.64106 5173.45441) (1036.95328 5187.33269) (1059.57760 5187.48111) (1082.20204 5173.45441)))
("SF_PLANTING" 0 ((1025.64095 4128.95928) (1067.11923 4132.73043)))
("SF_PLANTING" 0 ((1025.64095 3993.21267) (1078.43145 3993.21267)))
("SF_PLANTING" 0 ((1025.64095 3627.45057) (1055.80701 3627.45057)))
("SF_PLANTING" 0 ((1044.49480 3529.41176) (1023.07466 3514.32907) (1025.64095 3480.39242)))
("SF_PLANTING" 0 ((1025.64095 1172.70079) (1063.34842 1161.38857)))
("SF_PLANTING" 0 ((1025.64095 1172.70079) (1022.01833 1195.32523) (1029.41176 1225.48925)))
("SF_PLANTING" 0 ((1025.64095 690.04525) (1036.95317 693.81505)))
("SF_PLANTING" 0 ((1029.41176 3744.34389) (1048.26538 3748.11505)))
("SF_PLANTING" 0 ((1052.03620 1225.48925) (1029.41176 1225.48925)))
("SF_PLANTING" 0 ((1176.47059 3303.16742) (1157.61697 3306.93790) (1048.26538 3303.31584) (1033.18258 3310.70916)))
("SF_PLANTING" 0 ((1036.95317 3932.88043) (1097.28507 3917.79830)))
("SF_PLANTING" 0 ((1044.49480 3529.41176) (1070.88982 3506.78733)))
("SF_PLANTING" 0 ((1048.26538 967.19457) (1048.26538 935.14423)))
("SF_PLANTING" 0 ((1048.26538 967.19457) (1048.41357 1018.09955) (1055.80701 1033.18156)))
("SF_PLANTING" 0 ((1048.26538 967.19457) (1097.28507 969.08088)))
("SF_PLANTING" 0 ((1048.26538 935.14423) (1059.57771 931.52002) (1097.28507 931.37161)))
("SF_PLANTING" 0 ((1052.03620 1225.48925) (1063.35509 1206.78450) (1085.97285 1192.60973) (1112.36810 1187.93744)
(1131.22172 1199.09502)))
("SF_PLANTING" 0 ((1052.03620 1225.48925) (1062.14423 1240.57410) (1067.11923 1259.42590)))
("SF_PLANTING" 0 ((1108.59729 776.77319) (1089.74367 790.65034) (1052.03620 803.16742)))
("SF_PLANTING" 0 ((1052.03620 803.16742) (1052.18416 852.03281) (1055.80701 855.95871)))
("SF_PLANTING" 0 ((1070.88982 4068.62704) (1055.80701 4068.62704)))
("SF_PLANTING" 0 ((1074.66063 4034.69038) (1057.01131 4049.77376) (1055.80701 4068.62704)))
("SF_PLANTING" 0 ((1151.96086 3766.96833) (1123.68032 3763.34559) (1082.20204 3771.93676) (1055.80701 3785.82161)))
("SF_PLANTING" 0 ((1055.80701 3785.82161) (1055.95498 3812.21719) (1064.55260 3849.92500) (1092.30995 3876.32624)
(1097.28507 3917.79830)))
("SF_PLANTING" 0 ((1108.59729 3648.19005) (1093.36618 3617.34310) (1074.66063 3616.29367) (1055.80701 3627.45057)))
("SF_PLANTING" 0 ((1108.59729 3648.19005) (1074.66075 3652.78948) (1064.40464 3646.15667) (1055.80701 3627.45057)))
("SF_PLANTING" 0 ((1067.11923 1259.42590) (1055.80701 1297.13518)))
("SF_PLANTING" 0 ((1063.34842 1319.75962) (1055.80701 1297.13518)))
("SF_PLANTING" 0 ((1055.80701 855.95871) (1055.80701 878.58314)))
("SF_PLANTING" 0 ((1119.90950 893.66516) (1085.97285 893.51674) (1055.80701 878.58314)))
("SF_PLANTING" 0 ((1108.59729 837.10407) (1078.43145 851.13043) (1055.80701 855.95871)))
("SF_PLANTING" 0 ((1089.74367 1319.75962) (1063.34842 1319.75962)))
("SF_PLANTING" 0 ((1078.43145 1372.54808) (1071.03145 1368.62364) (1063.34842 1357.46606) (1063.34842 1319.75962)))
("SF_PLANTING" 0 ((1123.68032 509.04977) (1093.51425 505.42704) (1063.34842 512.81957)))
("SF_PLANTING" 0 ((1067.11923 4110.10600) (1067.11923 4132.73043)))
("SF_PLANTING" 0 ((1067.11923 4132.73043) (1074.66063 4144.04265) (1078.43145 4144.04265)))
("SF_PLANTING" 0 ((1070.88982 4068.62704) (1067.11923 4098.79378)))
("SF_ARCHITECTURE" 0 ((1067.11923 2352.94118) (1093.51425 2352.94118)))
("SF_ARCHITECTURE" 0 ((1067.11923 2352.94118) (1063.49638 2345.39321) (1063.34842 2322.77500) (1063.34842 2315.24027)
(1078.43145 2307.69231)))
("SF_PLANTING" 0 ((1093.51425 1259.42590) (1067.11923 1259.42590)))
("SF_ARCHITECTURE" 0 ((1070.88982 5663.65000) (1131.22172 5667.42081) (1165.15837 5663.65000)))
("SF_PLANTING" 0 ((1070.88982 4068.62704) (1085.97285 4061.08597)))
("SF_PLANTING" 0 ((1074.66063 4034.69038) (1074.80860 4012.07285) (1078.43145 4004.52489)))
("SF_PLANTING" 0 ((1074.66063 4034.69038) (1082.20204 4038.46154)))
("SF_PLANTING" 0 ((1074.66063 1108.59729) (1078.58609 1102.24593) (1093.51425 1097.28507)))
("SF_PLANTING" 0 ((1097.28507 1142.53394) (1083.40633 1134.98665) (1074.66063 1108.59729)))
("SF_PLANTING" 0 ((1097.28507 4140.27149) (1078.43145 4144.04265)))
("SF_ARCHITECTURE" 0 ((1082.20204 5173.45441) (1082.19548 4754.90238) (1078.43145 4728.50679) (1078.43801 4649.32127)
(1082.20204 4622.92568) (1078.43801 4419.30577) (1082.05407 4404.22364) (1082.19548 4340.12025) (1078.43801 4321.26697)
(1078.43145 4144.04265)))
("SF_PLANTING" 0 ((1078.43145 4004.52489) (1078.43145 3993.21267)))
("SF_PLANTING" 0 ((1078.43145 4004.52489) (1100.90113 4015.98518) (1104.82647 4027.14932)))
("SF_PLANTING" 0 ((1116.13869 3970.58824) (1089.89163 3979.18597) (1078.43145 3993.21267)))
("SF_ARCHITECTURE" 0 ((1078.43145 1372.54808) (1078.43145 2307.69231)))
("SF_ARCHITECTURE" 0 ((1078.43145 2307.69231) (1092.30995 2322.77500) (1093.51425 2352.94118)))
("SF_PLANTING" 0 ((1078.43145 1372.54808) (1089.58891 1357.46606) (1089.74367 1319.75962)))
("SF_ARCHITECTURE" 0 ((1082.20204 5173.45441) (1101.05588 5184.61165) (1142.53394 5180.99548)))
("SF_PLANTING" 0 ((1082.20204 4038.46154) (1104.82647 4027.14932)))
("SF_PLANTING" 0 ((1082.20204 4038.46154) (1085.97285 4061.08597)))
("SF_PLANTING" 0 ((1085.97285 4061.08597) (1104.82647 4064.85713)))
("SF_PLANTING" 0 ((1089.74367 1319.75962) (1097.13054 1270.73812) (1093.51425 1259.42590)))
("SF_PLANTING" 0 ((1089.74367 478.88292) (1089.74367 486.42534)))
("SF_ARCHITECTURE" 0 ((1142.53394 2352.94118) (1123.68032 2356.71165) (1101.06244 2356.56391) (1093.51425 2352.94118)))
("SF_PLANTING" 0 ((1093.51425 1259.42590) (1109.65351 1225.48925) (1131.22172 1206.63744)))
("SF_PLANTING" 0 ((1093.51425 1097.28507) (1085.97941 1021.86934) (1097.28507 969.08088)))
("SF_PLANTING" 0 ((1180.24140 1119.90950) (1138.76312 1118.86007) (1093.51425 1097.28507)))
("SF_PLANTING" 0 ((1097.28507 4140.27149) (1134.99242 4140.27149)))
("SF_PLANTING" 0 ((1097.28507 4140.27149) (1104.67851 4095.02262) (1104.82647 4064.85713)))
("SF_PLANTING" 0 ((1134.99253 3925.33937) (1123.68020 3917.95226) (1097.28507 3917.79830)))
("SF_PLANTING" 0 ((1101.05588 965.30826) (1101.05588 969.08088) (1097.28507 969.08088)))
("SF_PLANTING" 0 ((1097.28507 969.08088) (1101.05588 965.30826)))
("SF_PLANTING" 0 ((1097.28507 931.37161) (1119.90950 927.60181)))
("SF_PLANTING" 0 ((1097.28507 931.37161) (1101.05588 965.30826)))
("SF_PLANTING" 0 ((1108.59729 3665.15837) (1102.25351 3669.08348) (1101.05588 3687.78281)))
("SF_PLANTING" 0 ((1127.45090 3702.86618) (1108.60396 3697.89740) (1101.05588 3687.78281)))
("SF_PLANTING" 0 ((1101.05588 965.30826) (1127.45090 960.33360) (1138.76312 950.22624)))
("SF_PLANTING" 0 ((1112.36810 4057.31482) (1104.82647 4064.85713)))
("SF_PLANTING" 0 ((1112.36810 4030.92048) (1104.82647 4027.14932)))
("SF_PLANTING" 0 ((1108.59729 3648.19005) (1108.59729 3665.15837)))
("SF_PLANTING" 0 ((1127.45090 3702.86618) (1120.80452 3680.24174) (1108.59729 3665.15837)))
("SF_PLANTING" 0 ((1108.59729 3648.19005) (1138.76312 3646.30509)))
("SF_PLANTING" 0 ((1131.22172 818.24943) (1112.52274 826.84819) (1108.59729 837.10407)))
("SF_PLANTING" 0 ((1146.30475 863.49830) (1108.59729 837.10407)))
("SF_PLANTING" 0 ((1108.59729 776.77319) (1104.83959 761.68835) (1108.59729 723.98190)))
("SF_PLANTING" 0 ((1131.22172 780.54299) (1108.59729 776.77319)))
("SF_PLANTING" 0 ((1108.59729 663.65102) (1119.90950 671.19061)))
("SF_PLANTING" 0 ((1112.36810 4057.31482) (1134.99242 4057.31482)))
("SF_PLANTING" 0 ((1112.36810 4057.31482) (1112.36810 4030.92048)))
("SF_PLANTING" 0 ((1112.36810 4030.92048) (1148.19005 4032.80543)))
("SF_PLANTING" 0 ((1116.13869 3487.93337) (1112.36810 3480.39242)))
("SF_PLANTING" 0 ((1134.99253 3925.33937) (1120.96572 3944.19265) (1116.13869 3970.58824)))
("SF_PLANTING" 0 ((1116.13869 3970.58824) (1148.19005 4032.80543)))
("SF_PLANTING" 0 ((1116.13869 3487.93337) (1108.74525 3514.32907) (1108.74525 3552.03620) (1137.70701 3612.36776)
(1138.76312 3646.30509)))
("SF_PLANTING" 0 ((1116.13869 3487.93337) (1142.53394 3491.70464)))
("SF_PLANTING" 0 ((1134.99253 3280.54299) (1116.13869 3269.23077)))
("SF_PLANTING" 0 ((1116.13869 618.40215) (1131.22172 622.17195)))
("SF_PLANTING" 0 ((1119.90950 893.66516) (1119.90950 927.60181)))
("SF_PLANTING" 0 ((1119.90950 927.60181) (1138.76312 950.22624)))
("SF_PLANTING" 0 ((1119.90950 893.66516) (1134.99242 892.46719) (1146.30475 886.12274)))
("SF_PLANTING" 0 ((1119.90950 671.19061) (1138.76312 659.87839)))
("SF_PLANTING" 0 ((1119.90950 671.19061) (1121.11380 686.12014) (1138.76312 693.81505)))
("SF_PLANTING" 0 ((1123.68032 3838.61278) (1124.88462 3846.01233) (1142.53394 3861.23722)))
("SF_PLANTING" 0 ((1123.68032 509.04977) (1127.45090 565.61086)))
("SF_PLANTING" 0 ((1266.96833 512.81957) (1240.57308 509.05600) (1123.68032 509.04977)))
("SF_PLANTING" 0 ((1153.84615 3736.80283) (1138.91131 3725.48993) (1127.45090 3702.86618)))
("SF_PLANTING" 0 ((1150.07534 3404.97738) (1136.19027 3397.28100) (1127.45090 3378.58247)))
("SF_PLANTING" 0 ((1131.22172 1199.09502) (1131.22172 1206.63744)))
("SF_PLANTING" 0 ((1142.53394 1289.59276) (1142.37930 1221.71946) (1131.22172 1206.63744)))
("SF_PLANTING" 0 ((1168.92919 1180.24038) (1146.30475 1185.21640) (1131.22172 1199.09502)))
("SF_PLANTING" 0 ((1131.22172 1033.18156) (1150.07534 1018.25419) (1210.40724 1021.86934)))
("SF_PLANTING" 0 ((1131.22172 780.54299) (1131.22172 818.24943)))
("SF_PLANTING" 0 ((1150.07534 840.87387) (1131.22172 818.24943)))
("SF_PLANTING" 0 ((1134.99253 776.77319) (1134.99253 780.54299) (1131.22172 780.54299)))
("SF_PLANTING" 0 ((1134.99253 776.77319) (1131.22172 780.54299)))
("SF_PLANTING" 0 ((1161.38756 625.94174) (1138.76980 618.69762) (1131.22172 622.17195)))
("SF_PLANTING" 0 ((1138.76312 659.87839) (1131.22172 622.17195)))
("SF_PLANTING" 0 ((1134.99242 4121.41821) (1134.99242 4140.27149)))
("SF_PLANTING" 0 ((1142.53394 4174.20814) (1134.99242 4166.66018) (1134.99242 4140.27149)))
("SF_PLANTING" 0 ((1134.99242 4121.41821) (1153.69163 4120.21346) (1172.69977 4095.02262)))
("SF_PLANTING" 0 ((1134.99242 4121.41821) (1134.99242 4057.31482)))
("SF_PLANTING" 0 ((1146.30475 4049.77376) (1134.99242 4057.31482)))
("SF_PLANTING" 0 ((1134.99253 3925.33937) (1168.92919 3925.33937)))
("SF_PLANTING" 0 ((1199.09502 769.23077) (1134.99253 776.77319)))
("SF_PLANTING" 0 ((1134.99253 776.77319) (1135.14050 712.66968) (1138.76312 693.81505)))
("SF_PLANTING" 0 ((1153.84615 3646.30509) (1138.76312 3646.30509)))
("SF_PLANTING" 0 ((1199.09502 1346.15385) (1157.61686 1346.30158) (1138.76312 1349.92364)))
("SF_PLANTING" 0 ((1138.76312 1349.92364) (1131.36980 1338.61143) (1131.37636 1300.90498) (1142.53394 1289.59276)))
("SF_ARCHITECTURE" 0 ((1142.53394 2352.94118) (1142.52738 2269.98518) (1138.76968 2251.13122) (1138.76968 1896.68201)
(1142.53394 1870.28631) (1138.76968 1783.56052) (1142.52738 1764.70588) (1142.53394 1598.79242) (1138.76968 1572.39819)
(1138.76312 1349.92364)))
("SF_PLANTING" 0 ((1172.69977 950.22624) (1138.76312 950.22624)))
("SF_PLANTING" 0 ((1153.84615 682.50283) (1138.76312 693.81505)))
("SF_PLANTING" 0 ((1153.84615 682.50283) (1138.76312 659.87839)))
("SF_ARCHITECTURE" 0 ((1142.53394 4174.20814) (1134.99242 4245.85260) (1134.99242 4313.72590) (1142.53394 4336.35034)
(1142.52738 4939.66776) (1134.99242 4958.52229) (1142.23778 5000.00000) (1138.76968 5015.08337) (1138.76968 5131.97545)
(1142.53394 5180.99548)))
("SF_ARCHITECTURE" 0 ((1142.53394 5180.99548) (1176.47059 5188.38869) (1202.86584 5177.22432)))
("SF_PLANTING" 0 ((1142.53394 4174.20814) (1157.61697 4163.95260) (1172.69977 4160.17523) (1202.86584 4159.12477)))
("SF_PLANTING" 0 ((1193.43891 3472.85068) (1172.69977 3486.87704) (1142.53394 3491.70464)))
("SF_PLANTING" 0 ((1187.78281 3552.03620) (1172.69977 3554.60882) (1161.38756 3551.88778) (1146.45939 3540.72398)
(1139.05928 3518.09955) (1142.53394 3491.70464)))
("SF_ARCHITECTURE" 0 ((1142.53394 2352.94118) (1161.38756 2356.71165) (1184.00543 2356.56391) (1191.55362 2352.94118)))
("SF_PLANTING" 0 ((1157.61686 1308.44740) (1142.53394 1289.59276)))
("SF_PLANTING" 0 ((1146.30475 4049.77376) (1148.19005 4032.80543)))
("SF_PLANTING" 0 ((1146.30475 4049.77376) (1156.41923 4061.08597) (1162.43733 4079.93925) (1172.69977 4095.02262)))
("SF_PLANTING" 0 ((1191.55362 3461.53846) (1146.30475 3435.14355)))
("SF_PLANTING" 0 ((1146.30475 863.49830) (1146.30475 886.12274)))
("SF_PLANTING" 0 ((1176.47059 901.20758) (1146.30475 886.12274)))
("SF_PLANTING" 0 ((1146.30475 863.49830) (1150.07534 840.87387)))
("SF_PLANTING" 0 ((1195.32421 4042.23269) (1148.19005 4032.80543)))
("SF_PLANTING" 0 ((1206.63643 833.33428) (1165.15837 833.48201) (1150.07534 840.87387)))
("SF_PLANTING" 0 ((1151.96086 3766.96833) (1202.86584 3766.96833)))
("SF_PLANTING" 0 ((1151.96086 3766.96833) (1153.84615 3736.80283)))
("SF_PLANTING" 0 ((1151.96086 3766.96833) (1151.13156 3782.05170) (1162.58529 3808.44604) (1176.47059 3822.47274)
(1195.32421 3831.07048)))
("SF_PLANTING" 0 ((1153.84615 3736.80283) (1167.87285 3721.71946) (1172.69977 3710.40724)))
("SF_PLANTING" 0 ((1153.84615 3646.30509) (1184.01199 3646.30509)))
("SF_PLANTING" 0 ((1153.84615 3646.30509) (1158.67308 3668.92885) (1168.92919 3680.24174)))
("SF_PLANTING" 0 ((1210.40724 693.81505) (1153.84615 682.50283)))
("SF_PLANTING" 0 ((1187.78281 3412.51912) (1161.38756 3408.74785)))
("SF_PLANTING" 0 ((1168.92919 3925.33937) (1177.52014 3906.64005) (1184.01199 3902.71493)))
("SF_PLANTING" 0 ((1168.92919 3925.33937) (1180.24140 3947.96380)))
("SF_PLANTING" 0 ((1191.55362 3650.07500) (1190.34932 3668.92262) (1184.00543 3675.27296) (1168.92919 3680.24174)))
("SF_PLANTING" 0 ((1172.69977 3710.40724) (1168.92919 3680.24174)))
("SF_PLANTING" 0 ((1168.92919 1180.24038) (1169.08382 1146.30373) (1180.24140 1131.22172)))
("SF_PLANTING" 0 ((1199.09502 1259.42590) (1179.04367 1195.32523) (1168.92919 1180.24038)))
("SF_PLANTING" 0 ((1172.69977 4095.02262) (1206.63643 4098.79378)))
("SF_PLANTING" 0 ((1233.03167 3702.86618) (1206.63643 3703.02014) (1191.55362 3710.25260) (1172.69977 3710.40724)))
("SF_PLANTING" 0 ((1172.69977 950.22624) (1176.47059 931.37161)))
("SF_PLANTING" 0 ((1172.69977 950.22624) (1205.58020 984.16290) (1210.25916 995.47511) (1210.40724 1021.86934)))
("SF_PLANTING" 0 ((1176.47059 3303.16742) (1191.55362 3303.16742)))
("SF_PLANTING" 0 ((1176.47059 3303.16742) (1180.24140 3269.23077)))
("SF_PLANTING" 0 ((1248.11471 923.83201) (1221.71946 931.22455) (1176.47059 931.37161)))
("SF_PLANTING" 0 ((1176.47059 901.20758) (1176.47059 931.37161)))
("SF_PLANTING" 0 ((1176.47059 901.20758) (1225.49027 848.41629)))
("SF_PLANTING" 0 ((1180.24140 3959.27602) (1180.24140 3947.96380)))
("SF_PLANTING" 0 ((1255.65611 3959.27602) (1221.71946 3948.11188) (1180.24140 3947.96380)))
("SF_PLANTING" 0 ((1180.24140 1119.90950) (1180.24140 1131.22172)))
("SF_PLANTING" 0 ((1199.09502 1138.76414) (1180.24140 1131.22172)))
("SF_PLANTING" 0 ((1180.24140 1119.90950) (1199.09502 1098.34140) (1221.71946 1089.74265)))
("SF_PLANTING" 0 ((1248.11471 3883.86165) (1210.40724 3897.89423) (1184.01199 3902.71493)))
("SF_PLANTING" 0 ((1195.32421 3842.38269) (1184.16007 3887.63156) (1184.01199 3902.71493)))
("SF_PLANTING" 0 ((1187.78281 3612.36776) (1184.01199 3646.30509)))
("SF_PLANTING" 0 ((1191.55362 3650.07500) (1184.01199 3646.30509)))
("SF_PLANTING" 0 ((1187.78281 3612.36776) (1217.79400 3607.39932) (1221.71946 3601.05554)))
("SF_PLANTING" 0 ((1187.78281 3612.36776) (1181.29106 3601.05554) (1180.39604 3582.20238) (1191.55362 3570.89016)))
("SF_PLANTING" 0 ((1187.78281 3552.03620) (1191.55362 3540.72398)))
("SF_PLANTING" 0 ((1187.78281 3552.03620) (1191.55362 3570.89016)))
("SF_PLANTING" 0 ((1187.78281 3412.51912) (1194.95577 3394.71459) (1187.78281 3363.49898)))
("SF_PLANTING" 0 ((1187.78281 3412.51912) (1195.32421 3435.14355)))
("SF_PLANTING" 0 ((1187.78281 3363.49898) (1195.32749 3362.29491) (1202.49050 3353.23631) (1191.55362 3340.87455)))
("SF_PLANTING" 0 ((1187.78281 3363.49898) (1180.39604 3359.57387) (1177.82964 3352.18676) (1191.55362 3340.87455)))
("SF_PLANTING" 0 ((1191.55362 3235.29412) (1187.78281 3205.12794)))
("SF_PLANTING" 0 ((1233.03167 3650.07500) (1191.55362 3650.07500)))
("SF_PLANTING" 0 ((1221.71946 3601.05554) (1202.86584 3578.43801) (1191.55362 3570.89016)))
("SF_PLANTING" 0 ((1233.03167 3540.72398) (1191.55362 3540.72398)))
("SF_PLANTING" 0 ((1193.43891 3472.85068) (1195.31765 3525.64129) (1191.55362 3540.72398)))
("SF_PLANTING" 0 ((1191.55362 3461.53846) (1195.32421 3435.14355)))
("SF_PLANTING" 0 ((1191.55362 3461.53846) (1193.43891 3472.85068)))
("SF_PLANTING" 0 ((1191.55362 3303.16742) (1191.55362 3340.87455)))
("SF_PLANTING" 0 ((1191.55362 3303.16742) (1199.10170 3299.54468) (1236.80249 3299.39695)))
("SF_ARCHITECTURE" 0 ((1191.55362 2352.94118) (1210.40724 2352.94118)))
("SF_ARCHITECTURE" 0 ((1191.55362 2352.94118) (1189.13507 2269.99140) (1199.09502 2262.44344)))
("SF_PLANTING" 0 ((1193.43891 3472.85068) (1225.48360 3477.82534) (1231.82738 3484.16980) (1233.03167 3540.72398)))
("SF_PLANTING" 0 ((1195.32421 4042.23269) (1210.41380 4023.53314) (1225.49016 4018.09106) (1235.59819 4027.14932)
(1240.57308 4049.77376)))
("SF_PLANTING" 0 ((1195.32421 4042.23269) (1195.47229 4064.85713) (1206.63643 4098.79378)))
("SF_PLANTING" 0 ((1195.32421 3842.38269) (1248.11471 3842.38269)))
("SF_PLANTING" 0 ((1195.32421 3842.38269) (1195.32421 3831.07048)))
("SF_PLANTING" 0 ((1202.86584 3766.96833) (1202.71776 3812.21719) (1195.32421 3831.07048)))
("SF_PLANTING" 0 ((1195.32421 3435.14355) (1217.94864 3430.16821) (1228.05656 3420.06007) (1236.65441 3378.58247)
(1233.04480 3333.33360) (1236.80249 3299.39695)))
("SF_ARCHITECTURE" 0 ((1199.09502 1346.15385) (1199.09502 2262.44344)))
("SF_ARCHITECTURE" 0 ((1210.40724 2352.94118) (1214.17794 2330.31674) (1214.17794 2277.52613) (1199.09502 2262.44344)))
("SF_PLANTING" 0 ((1199.09502 1259.42590) (1199.09502 1346.15385)))
("SF_PLANTING" 0 ((1199.09502 1259.42590) (1244.34389 1271.93676) (1259.42692 1285.82296)))
("SF_PLANTING" 0 ((1199.09502 1138.76414) (1225.49027 1138.76414)))
("SF_PLANTING" 0 ((1199.09502 1138.76414) (1200.29921 1146.31131) (1222.91708 1180.23552) (1233.03167 1187.78281)))
("SF_PLANTING" 0 ((1199.09502 769.23077) (1206.64310 758.07941) (1214.17805 755.35215) (1229.26086 758.97489)
(1251.88529 773.00057)))
("SF_PLANTING" 0 ((1199.09502 769.23077) (1206.63643 833.33428)))
("SF_ARCHITECTURE" 0 ((1202.86584 5177.22432) (1199.09502 5135.74661) (1199.10158 4185.52036) (1202.86584 4159.12477)))
("SF_ARCHITECTURE" 0 ((1259.42692 5180.99548) (1240.57308 5188.38869) (1225.49027 5188.38869) (1202.86584 5177.22432)))
("SF_PLANTING" 0 ((1202.86584 4159.12477) (1206.48846 4151.57749) (1206.63643 4098.79378)))
("SF_PLANTING" 0 ((1202.86584 3766.96833) (1233.03167 3763.19717)))
("SF_PLANTING" 0 ((1210.40724 3235.29412) (1209.20962 3246.60011) (1202.86584 3254.14808)))
("SF_PLANTING" 0 ((1206.63643 4098.79378) (1248.10814 4107.53903) (1259.42692 4117.64706)))
("SF_PLANTING" 0 ((1206.63643 833.33428) (1225.49027 848.41629)))
("SF_ARCHITECTURE" 0 ((1255.65611 2352.94118) (1240.57308 2356.71165) (1217.95532 2356.56391) (1210.40724 2352.94118)))
("SF_PLANTING" 0 ((1221.71946 1044.49378) (1210.40724 1021.86934)))
("SF_PLANTING" 0 ((1229.26086 467.57070) (1210.40724 467.57070)))
("SF_PLANTING" 0 ((1229.26086 3601.05554) (1221.71946 3601.05554)))
("SF_PLANTING" 0 ((1221.71946 1044.49378) (1221.71946 1089.74265)))
("SF_PLANTING" 0 ((1251.88529 1108.59729) (1244.19581 1094.71867) (1221.71946 1089.74265)))
("SF_PLANTING" 0 ((1221.71946 1044.49378) (1236.80238 1039.52602) (1247.05837 1029.41176) (1255.65611 995.47511)))
("SF_PLANTING" 0 ((1251.88529 1108.59729) (1225.49027 1138.76414)))
("SF_PLANTING" 0 ((1282.05136 1176.47059) (1244.34389 1160.18993) (1225.49027 1138.76414)))
("SF_PLANTING" 0 ((1248.11471 848.41629) (1225.49027 848.41629)))
("SF_PLANTING" 0 ((1229.26086 3601.05554) (1236.64785 3589.74333) (1240.57308 3548.26572)))
("SF_PLANTING" 0 ((1229.26086 3601.05554) (1240.57308 3612.36776)))
("SF_PLANTING" 0 ((1233.03167 3763.19717) (1240.42511 3744.34389) (1240.57308 3706.63609)))
("SF_PLANTING" 0 ((1233.03167 3763.19717) (1248.11471 3774.50939)))
("SF_PLANTING" 0 ((1233.03167 3702.86618) (1233.03167 3650.07500)))
("SF_PLANTING" 0 ((1233.03167 3702.86618) (1240.57308 3706.63609)))
("SF_PLANTING" 0 ((1233.03167 3650.07500) (1240.57308 3612.36776)))
("SF_PLANTING" 0 ((1240.57308 3548.26572) (1233.03167 3540.72398)))
("SF_PLANTING" 0 ((1236.80249 3299.39695) (1255.65611 3299.39695)))
("SF_PLANTING" 0 ((1282.05136 3676.47059) (1251.88541 3701.80950) (1240.57308 3706.63609)))
("SF_PLANTING" 0 ((1240.57308 3612.36776) (1251.88529 3604.82681)))
("SF_PLANTING" 0 ((1240.57308 3548.26572) (1263.19751 3539.66765) (1280.99502 3521.87002) (1285.67387 3510.55781)
(1285.82195 3476.62115)))
("SF_PLANTING" 0 ((1248.11471 3883.86165) (1248.11471 3842.38269)))
("SF_PLANTING" 0 ((1248.11471 3883.86165) (1274.51301 3884.01256) (1287.70747 3889.51776)))
("SF_PLANTING" 0 ((1285.82195 3842.38269) (1248.11471 3842.38269)))
("SF_PLANTING" 0 ((1248.11471 3793.36391) (1244.34389 3812.21719) (1248.11471 3842.38269)))
("SF_PLANTING" 0 ((1248.11471 3793.36391) (1248.11471 3774.50939)))
("SF_PLANTING" 0 ((1248.11471 3793.36391) (1259.42692 3797.13382)))
("SF_PLANTING" 0 ((1248.11471 3774.50939) (1255.66278 3768.15939) (1289.59276 3755.65611)))
("SF_PLANTING" 0 ((1248.11471 1217.94966) (1255.66278 1221.42330) (1266.96833 1219.14683) (1293.36357 1222.92432)
(1308.44638 1234.91799)))
("SF_PLANTING" 0 ((1248.11471 923.83201) (1251.88529 882.35294) (1248.11471 848.41629)))
("SF_PLANTING" 0 ((1248.11471 923.83201) (1248.26267 972.85068) (1255.65611 995.47511)))
("SF_PLANTING" 0 ((1248.11471 848.41629) (1255.65611 840.87387)))
("SF_PLANTING" 0 ((1251.88529 1108.59729) (1270.73914 1108.59729)))
("SF_PLANTING" 0 ((1287.70747 759.80486) (1270.73914 771.94491) (1251.88529 773.00057)))
("SF_PLANTING" 0 ((1255.65611 840.87387) (1251.88529 773.00057)))
("SF_PLANTING" 0 ((1251.88529 622.17195) (1259.42692 618.40215)))
("SF_PLANTING" 0 ((1266.96833 3959.27602) (1255.65611 3959.27602)))
("SF_PLANTING" 0 ((1255.65611 3959.27602) (1252.94163 3981.90045) (1282.05136 4034.69038)))
("SF_PLANTING" 0 ((1255.65611 3299.39695) (1267.11629 3276.77229) (1282.05136 3276.77229)))
("SF_PLANTING" 0 ((1282.05136 3303.16742) (1255.65611 3299.39695)))
("SF_ARCHITECTURE" 0 ((1255.65611 2352.94118) (1255.66267 1304.67477) (1259.42692 1285.82296)))
("SF_ARCHITECTURE" 0 ((1255.65611 2352.94118) (1274.50973 2356.71165) (1300.90498 2352.94118)))
("SF_PLANTING" 0 ((1293.36357 976.62048) (1255.65611 995.47511)))
("SF_PLANTING" 0 ((1255.65611 840.87387) (1293.36357 840.87387)))
("SF_ARCHITECTURE" 0 ((1259.42692 5180.99548) (1259.42036 4690.79898) (1255.65611 4664.40464) (1255.66267 4132.73043)
(1259.42692 4117.64706)))
("SF_ARCHITECTURE" 0 ((1259.42692 5180.99548) (1300.90498 5184.76663)))
("SF_PLANTING" 0 ((1293.36357 4098.79378) (1259.42692 4117.64706)))
("SF_PLANTING" 0 ((1278.28054 1285.82296) (1259.42692 1285.82296)))
("SF_PLANTING" 0 ((1266.96833 629.71437) (1259.42692 671.19061)))
("SF_PLANTING" 0 ((1274.50973 701.35747) (1259.57500 696.38903) (1254.76109 690.03835) (1252.04649 678.73993)
(1259.42692 671.19061)))
("SF_PLANTING" 0 ((1285.82195 693.81505) (1259.42692 671.19061)))
("SF_PLANTING" 0 ((1263.19751 599.54751) (1259.42692 618.40215)))
("SF_PLANTING" 0 ((1266.96833 629.71437) (1259.42692 618.40215)))
("SF_PLANTING" 0 ((1266.96833 512.81957) (1259.57500 554.29864) (1263.19751 569.38066)))
("SF_PLANTING" 0 ((1266.96833 3959.27602) (1268.02455 3944.19265) (1287.70747 3889.51776)))
("SF_PLANTING" 0 ((1297.13416 3963.04717) (1274.51640 3962.89876) (1266.96833 3959.27602)))
("SF_PLANTING" 0 ((1266.96833 3469.08020) (1285.82195 3476.62115)))
("SF_PLANTING" 0 ((1282.05136 633.48416) (1278.28054 629.71437) (1266.96833 629.71437)))
("SF_PLANTING" 0 ((1266.96833 512.81957) (1282.05136 509.05600) (2220.96505 505.27907)))
("SF_PLANTING" 0 ((1353.69525 1052.03620) (1285.82195 1094.57093) (1270.73914 1108.59729)))
("SF_PLANTING" 0 ((1270.73914 1108.59729) (1278.28722 1119.76176) (1293.36357 1127.45192)))
("SF_PLANTING" 0 ((1304.67579 1003.01753) (1283.24898 1033.18156) (1270.73914 1063.34842)))
("SF_PLANTING" 0 ((1274.50973 701.35747) (1285.82195 693.81505)))
("SF_PLANTING" 0 ((1274.50973 701.35747) (1274.65792 742.83654) (1279.40419 754.06731) (1287.70747 759.80486)))
("SF_PLANTING" 0 ((1278.28054 1285.82296) (1290.64910 1259.57432) (1304.67579 1248.11369)))
("SF_PLANTING" 0 ((1278.28054 1285.82296) (1308.44638 1293.36256)))
("SF_PLANTING" 0 ((1297.13416 565.61086) (1278.28054 580.69287)))
("SF_PLANTING" 0 ((1327.30023 4032.80543) (1282.05136 4034.69038)))
("SF_PLANTING" 0 ((1293.36357 4098.79378) (1282.19943 4076.16934) (1278.57670 4042.23891) (1282.05136 4034.69038)))
("SF_PLANTING" 0 ((1308.44638 3676.47059) (1282.05136 3676.47059)))
("SF_PLANTING" 0 ((1282.05136 3676.47059) (1283.11414 3642.68857) (1312.21719 3633.10667)))
("SF_PLANTING" 0 ((1282.05136 3303.16742) (1934.38914 3303.16120) (1945.70136 3299.39695)))
("SF_PLANTING" 0 ((1282.05136 3303.16742) (1282.05136 3276.77229)))
("SF_PLANTING" 0 ((1542.23224 3276.77229) (1282.05136 3276.77229)))
("SF_PLANTING" 0 ((1285.82195 3842.38269) (1297.28235 3824.57919) (1319.75860 3812.36527) (1349.92466 3817.04378)
(1383.86131 3834.84163)))
("SF_PLANTING" 0 ((1285.82195 3842.38269) (1287.70747 3889.51776)))
("SF_PLANTING" 0 ((1285.82195 3476.62115) (1296.97964 3471.79434) (1300.75034 3465.30271) (1299.84876 3446.45577)
(1293.36357 3435.14355)))
("SF_PLANTING" 0 ((1285.82195 3438.91403) (1293.36357 3435.14355)))
("SF_PLANTING" 0 ((1285.82195 693.81505) (1300.90498 693.81505)))
("SF_PLANTING" 0 ((1349.92466 3891.40271) (1287.70747 3889.51776)))
("SF_PLANTING" 0 ((1287.70747 759.80486) (1304.67579 746.60633)))
("SF_PLANTING" 0 ((1287.70747 759.80486) (1301.05305 784.16572) (1315.98801 791.85520)))
("SF_PLANTING" 0 ((1300.90498 3721.71946) (1290.64253 3740.57274) (1289.59276 3755.65611)))
("SF_PLANTING" 0 ((1289.59276 3755.65611) (1308.44638 3763.04932) (1421.56855 3763.19717)))
("SF_PLANTING" 0 ((1293.36357 4098.79378) (1308.44638 4102.56369)))
("SF_PLANTING" 0 ((1297.13416 3412.51912) (1300.74389 3423.83133) (1293.36357 3435.14355)))
("SF_PLANTING" 0 ((1342.38303 1131.22172) (1323.52941 1120.05792) (1300.91165 1120.06414) (1293.36357 1127.45192)))
("SF_PLANTING" 0 ((1293.36357 1127.45192) (1301.05305 1146.29887) (1319.75860 1157.61595)))
("SF_PLANTING" 0 ((1300.90498 931.37161) (1293.36357 976.62048)))
("SF_PLANTING" 0 ((1304.67579 1003.01753) (1303.47149 991.70532) (1293.36357 976.62048)))
("SF_PLANTING" 0 ((1293.36357 840.87387) (1311.01946 818.24943) (1315.98801 791.85520)))
("SF_PLANTING" 0 ((1300.90498 931.37161) (1308.29830 882.35294) (1303.47149 855.95871) (1293.36357 840.87387)))
("SF_PLANTING" 0 ((1297.13416 3963.04717) (1312.21719 3945.39050) (1349.92455 3928.05385) (1361.23688 3917.79830)))
("SF_PLANTING" 0 ((1297.13416 3963.04717) (1304.67579 3974.35939) (1308.44638 3974.35939)))
("SF_PLANTING" 0 ((1308.44638 603.31731) (1297.13416 595.77771)))
("SF_ARCHITECTURE" 0 ((1300.90498 5184.76663) (1319.75204 5184.61165) (1326.09593 5180.84084) (1327.30023 5120.66324)))
("SF_ARCHITECTURE" 0 ((1300.90498 5184.76663) (1300.90498 5060.33224) (1315.98801 5049.02002)))
("SF_ARCHITECTURE" 0 ((1300.90498 2352.94118) (1319.75204 2352.78654) (1326.09593 2349.01606) (1327.15215 2315.23405)
(1323.52941 2303.92183)))
("SF_ARCHITECTURE" 0 ((1300.90498 2352.94118) (1300.90498 2303.92183)))
("SF_ARCHITECTURE" 0 ((1300.90498 2303.92183) (1323.52941 2303.92183)))
("SF_ARCHITECTURE" 0 ((1312.21719 2273.75566) (1302.10916 2281.30362) (1300.90498 2303.92183)))
("SF_PLANTING" 0 ((1372.54910 935.14423) (1365.00090 931.52002) (1300.90498 931.37161)))
("SF_PLANTING" 0 ((1300.90498 693.81505) (1300.90498 667.42081)))
("SF_PLANTING" 0 ((1300.90498 693.81505) (1312.21719 712.66968)))
("SF_PLANTING" 0 ((1308.44638 1234.91799) (1304.67579 1248.11369)))
("SF_PLANTING" 0 ((1308.44638 1293.36256) (1315.83337 1282.05034) (1315.83326 1263.19853) (1304.67579 1248.11369)))
("SF_PLANTING" 0 ((1334.84163 1003.01753) (1304.67579 1003.01753)))
("SF_PLANTING" 0 ((1331.07081 4053.54491) (1326.24389 4079.93925) (1308.44638 4102.56369)))
("SF_PLANTING" 0 ((1308.44638 4102.56369) (1308.59446 4155.19989) (1312.21719 4159.12477)))
("SF_PLANTING" 0 ((1308.44638 3974.35939) (1323.52941 3970.73631) (1372.54910 3970.58824)))
("SF_PLANTING" 0 ((1308.44638 3974.35939) (1309.64412 3996.98382) (1327.30023 4032.80543)))
("SF_PLANTING" 0 ((1308.44638 3676.47059) (1312.21719 3633.10667)))
("SF_PLANTING" 0 ((1308.44638 3676.47059) (1315.99457 3682.81437) (1327.30023 3684.01165)))
("SF_PLANTING" 0 ((1308.44638 1293.36256) (1312.21719 1349.92364)))
("SF_PLANTING" 0 ((1334.84163 1176.47059) (1317.03767 1206.63744) (1308.44638 1234.91799)))
("SF_PLANTING" 0 ((1308.44638 1234.91799) (1368.77828 1240.57410)))
("SF_PLANTING" 0 ((1319.75860 595.77771) (1308.44638 603.31731)))
("SF_PLANTING" 0 ((1312.21719 625.94174) (1308.44638 603.31731)))
("SF_PLANTING" 0 ((1365.00747 4159.12477) (1312.21719 4159.12477)))
("SF_ARCHITECTURE" 0 ((1315.98801 5049.02002) (1312.21719 4159.12477)))
("SF_PLANTING" 0 ((1331.07081 3627.45057) (1312.21719 3633.10667)))
("SF_PLANTING" 0 ((1312.21719 3559.57794) (1308.44661 3601.05554) (1312.21719 3633.10667)))
("SF_ARCHITECTURE" 0 ((1312.21719 2273.75566) (1312.21719 1349.92364)))
("SF_ARCHITECTURE" 0 ((1312.21719 2273.75566) (1327.30023 2296.38009)))
("SF_PLANTING" 0 ((1312.21719 1349.92364) (1368.77828 1346.15385)))
("SF_ARCHITECTURE" 0 ((1315.98801 5049.02002) (1327.30011 5064.10215) (1327.30023 5120.66324)))
("SF_PLANTING" 0 ((1361.23688 727.75170) (1343.43925 750.37613) (1326.24400 784.30792) (1315.98801 791.85520)))
("SF_PLANTING" 0 ((1342.38303 1131.22172) (1319.75860 1157.61595)))
("SF_PLANTING" 0 ((1334.84163 1176.47059) (1319.75860 1157.61595)))
("SF_ARCHITECTURE" 0 ((1327.30023 2296.38009) (1323.52941 2303.92183)))
("SF_ARCHITECTURE" 0 ((1760.93518 5324.28314) (1685.52036 5311.92138) (1576.16889 5277.97885) (1466.81753 5221.41776)
(1387.63190 5161.99378) (1349.92466 5125.63201) (1327.30023 5120.66324)))
("SF_PLANTING" 0 ((1370.66357 4044.11765) (1353.69536 4031.07443) (1327.30023 4032.80543)))
("SF_PLANTING" 0 ((1331.07081 4053.54491) (1327.30023 4032.80543)))
("SF_ARCHITECTURE" 0 ((1760.93518 2503.77048) (1753.38710 2500.14774) (1719.45701 2499.85226) (1666.66663 2487.63835)
(1561.08597 2449.78959) (1451.73450 2389.59265) (1398.94412 2349.02217) (1353.69525 2304.97817) (1327.30023
2296.38009)))
("SF_PLANTING" 0 ((1331.07081 4053.54491) (1361.23688 4057.31482)))
("SF_PLANTING" 0 ((1447.96380 3533.18224) (1429.11018 3536.95351) (1365.00747 3536.80577) (1342.38314 3533.18846)
(1331.07081 3536.95351)))
("SF_PLANTING" 0 ((1334.84163 1176.47059) (1342.38303 1176.47059)))
("SF_PLANTING" 0 ((1372.54910 935.14423) (1371.49287 946.45645) (1360.18722 969.08088) (1334.84163 1003.01753)))
("SF_PLANTING" 0 ((1353.69525 1021.86934) (1342.38959 1014.32217) (1334.84163 1003.01753)))
("SF_PLANTING" 0 ((1366.89299 1133.10803) (1354.75475 1146.30170) (1342.38303 1176.47059)))
("SF_PLANTING" 0 ((1383.86131 1214.17704) (1372.54242 1191.70792) (1342.38303 1176.47059)))
("SF_PLANTING" 0 ((1342.38303 1131.22172) (1366.89299 1133.10803)))
("SF_PLANTING" 0 ((1349.92466 3891.40271) (1357.47274 3881.14027) (1380.09050 3868.77828)))
("SF_PLANTING" 0 ((1349.92466 3891.40271) (1361.23688 3917.79830)))
("SF_PLANTING" 0 ((1349.92466 3363.49898) (1357.47274 3367.12251) (1402.71493 3367.27025)))
("SF_PLANTING" 0 ((1349.92466 852.18609) (1368.77828 814.47964)))
("SF_PLANTING" 0 ((1365.00747 686.27545) (1357.46606 693.81505) (1349.92466 693.81505)))
("SF_PLANTING" 0 ((1447.96380 3476.62115) (1391.40271 3472.85068) (1353.69525 3476.62115)))
("SF_PLANTING" 0 ((1353.69525 1052.03620) (1353.69525 1021.86934)))
("SF_PLANTING" 0 ((1353.69525 1052.03620) (1398.94412 1055.80600)))
("SF_PLANTING" 0 ((1353.69525 1021.86934) (1383.86131 1018.25419) (1402.71493 1025.64197)))
("SF_PLANTING" 0 ((1357.46606 3401.20667) (1451.73450 3401.20667)))
("SF_PLANTING" 0 ((1370.66357 4044.11765) (1361.23688 4057.31482)))
("SF_PLANTING" 0 ((1365.00747 4159.12477) (1368.63032 4151.57749) (1368.77172 4113.87590) (1361.23688 4057.31482)))
("SF_PLANTING" 0 ((1361.23688 3917.79830) (1410.25633 3917.79830)))
("SF_PLANTING" 0 ((1681.74966 3435.14333) (1372.54910 3435.14333) (1361.23688 3435.14333)))
("SF_ARCHITECTURE" 0 ((1557.31527 5199.84876) (1546.00294 5198.79265) (1523.37862 5187.33925) (1451.73450 5135.59853)
(1372.54898 5071.49604) (1372.54898 5052.78993) (1372.54898 4803.92115) (1372.54898 4785.06787) (1368.77172 4174.20814)
(1365.00747 4159.12477)))
("SF_PLANTING" 0 ((1365.00747 3687.78281) (1391.40271 3687.78281)))
("SF_PLANTING" 0 ((1398.94412 1097.28507) (1380.23857 1108.60351) (1366.89299 1133.10803)))
("SF_PLANTING" 0 ((1398.94412 1165.15837) (1383.85464 1146.30373) (1366.89299 1133.10803)))
("SF_PLANTING" 0 ((1368.77828 1240.57410) (1368.77828 1346.15385)))
("SF_ARCHITECTURE" 0 ((1395.17353 2266.21391) (1373.74683 2243.58948) (1368.78484 2224.73631) (1368.77828 1365.00848)
(1368.77828 1346.15385)))
("SF_PLANTING" 0 ((1368.77828 1240.57410) (1375.27014 1236.64819) (1383.86131 1214.17704)))
("SF_PLANTING" 0 ((2077.67749 629.71437) (2058.82353 633.48416) (1368.77828 629.71437)))
("SF_PLANTING" 0 ((1368.77828 595.77771) (1398.94412 592.01199) (1485.67115 595.77771) (1508.29559 592.01199)
(1723.22771 592.00509)))
("SF_PLANTING" 0 ((1395.17353 4004.52489) (1382.80181 4030.92296) (1370.66357 4044.11765)))
("SF_PLANTING" 0 ((1414.02715 4046.00260) (1402.71482 4052.48824) (1391.40271 4053.39649) (1370.66357 4044.11765)))
("SF_PLANTING" 0 ((1372.54910 3970.58824) (1391.25475 3955.49864) (1414.02715 3925.33937)))
("SF_PLANTING" 0 ((1395.17353 4004.52489) (1381.14661 3989.29367) (1372.54910 3970.58824)))
("SF_PLANTING" 0 ((1372.54910 935.14423) (1440.42229 935.14333)))
("SF_PLANTING" 0 ((1391.40271 3582.20238) (1380.09050 3582.20238) (1376.31968 3578.43111)))
("SF_PLANTING" 0 ((1376.31968 569.38156) (1478.12975 569.38156) (1500.75419 569.38156) (1745.85215 569.38156)
(1768.47658 569.38156) (1794.87183 569.38156) (1892.91075 569.38156) (1915.53518 569.38066) (2081.44796 573.14638)
(2092.76018 569.38066)))
("SF_PLANTING" 0 ((1380.09050 3868.77828) (1383.86131 3834.84163)))
("SF_PLANTING" 0 ((1380.09050 3868.77828) (1391.25475 3876.32624) (1401.66516 3891.40271) (1410.25633 3917.79830)))
("SF_PLANTING" 0 ((1398.94412 3834.84163) (1383.86131 3834.84163)))
("SF_PLANTING" 0 ((1451.73450 1210.40724) (1417.79796 1206.78450) (1383.86131 1214.17704)))
("SF_PLANTING" 0 ((1395.17353 4004.52489) (1417.79796 4004.52489)))
("SF_ARCHITECTURE" 0 ((1402.71493 2262.44344) (1395.17353 2266.21391)))
("SF_ARCHITECTURE" 0 ((1395.17353 2266.21391) (1406.48575 2281.29740)))
("SF_PLANTING" 0 ((1398.94412 1165.15837) (1395.17353 1176.47059)))
("SF_PLANTING" 0 ((1398.94412 3834.84163) (1421.56855 3763.19717)))
("SF_PLANTING" 0 ((1463.04672 3855.58111) (1398.94412 3834.84163)))
("SF_PLANTING" 0 ((1398.94412 1165.15837) (1414.02715 1161.53563) (1455.50532 1161.38857)))
("SF_PLANTING" 0 ((1398.94412 1097.28507) (1398.94412 1055.80600)))
("SF_PLANTING" 0 ((1398.94412 1097.28507) (1432.88077 1111.31143) (1455.50532 1112.36708)))
("SF_PLANTING" 0 ((1402.71493 1052.03620) (1402.71493 1055.80600) (1398.94412 1055.80600)))
("SF_PLANTING" 0 ((1402.71493 1052.03620) (1398.94412 1055.80600)))
("SF_PLANTING" 0 ((1402.71493 4144.04265) (1406.48575 4166.66708)))
("SF_PLANTING" 0 ((1402.71493 1052.03620) (1402.71493 1033.18156)))
("SF_PLANTING" 0 ((1444.19310 1048.26640) (1429.11018 1055.65271) (1402.71493 1052.03620)))
("SF_PLANTING" 0 ((1402.71493 1033.18156) (1406.48575 1033.18156) (1410.25633 1025.64197)))
("SF_PLANTING" 0 ((1402.71493 1025.64197) (1402.71493 1033.18156)))
("SF_PLANTING" 0 ((1402.71493 1025.64197) (1410.25633 1025.64197)))
("SF_ARCHITECTURE" 0 ((1421.56855 2269.98518) (1406.48575 2281.29740)))
("SF_ARCHITECTURE" 0 ((1772.24740 2450.98066) (1753.39367 2450.83292) (1659.12523 2427.30667) (1568.62749 2393.37002)
(1463.04672 2333.03088) (1406.48575 2281.29740)))
("SF_PLANTING" 0 ((1414.02715 3925.33937) (1410.25633 3917.79830)))
("SF_PLANTING" 0 ((1504.52489 1033.18156) (1478.12975 1028.35543) (1459.27602 1015.53314) (1436.65158 1010.71244)
(1421.56867 1015.38541) (1410.25633 1025.64197)))
("SF_PLANTING" 0 ((1474.35894 878.58314) (1417.80452 882.50068) (1410.25633 886.12274)))
("SF_PLANTING" 0 ((1414.02715 3925.33937) (1432.88077 3932.73258) (1474.35894 3932.88043)))
("SF_PLANTING" 0 ((2073.90622 754.14876) (2043.74084 750.38303) (1979.63801 750.52455) (1964.55532 754.14186)
(1447.96380 754.14876) (1414.02715 750.37613)))
("SF_PLANTING" 0 ((1417.79796 4030.92048) (1421.72330 4020.05848) (1417.79796 4004.52489)))
("SF_PLANTING" 0 ((1417.79796 4004.52489) (1432.88077 3990.64627) (1447.96380 3989.44152)))
("SF_PLANTING" 0 ((1436.65158 3755.65611) (1421.56855 3763.19717)))
("SF_PLANTING" 0 ((1421.56855 1255.65611) (1425.49400 1245.54876) (1451.73450 1236.80147)))
("SF_PLANTING" 0 ((2043.74084 855.95871) (2024.88688 852.19989) (2009.80419 855.66176) (1998.49197 852.33450)
(1855.20362 852.18122) (1832.57919 848.41629) (1798.64253 852.18122) (1662.89593 852.33450) (1647.81301 855.95181)
(1421.56855 855.95871)))
("SF_PLANTING" 0 ((2081.44796 693.81505) (2070.13575 690.05147) (1429.11018 690.04525)))
("SF_PLANTING" 0 ((2036.19910 814.47964) (2017.34514 806.94412) (1444.19310 805.42104) (1432.88077 814.47964)))
("SF_PLANTING" 0 ((1436.65158 3755.65611) (1432.88744 3744.34389) (1436.49706 3725.49061) (1433.02885 3710.40724)
(1433.02885 3634.99287) (1440.27421 3612.36776) (1441.62002 3589.75023) (1447.96380 3582.20238)))
("SF_PLANTING" 0 ((1436.65158 3755.65611) (1481.90045 3764.86934) (1523.37862 3763.19717)))
("SF_PLANTING" 0 ((2104.07240 931.37161) (2088.98971 935.14333) (1440.42229 935.14333)))
("SF_PLANTING" 0 ((1440.42229 935.14333) (1440.57692 957.76867) (1444.34774 965.16120) (1455.50520 970.74480)
(1466.81753 969.08088)))
("SF_ARCHITECTURE" 0 ((1459.27602 5003.77115) (1444.19310 5022.62443)))
("SF_PLANTING" 0 ((1478.12975 3974.35939) (1447.96380 3989.44152)))
("SF_PLANTING" 0 ((1451.73450 4034.69038) (1447.96380 3989.44152)))
("SF_PLANTING" 0 ((1447.96380 3476.62115) (1447.96380 3533.18224)))
("SF_PLANTING" 0 ((1704.37410 3533.18224) (1489.44197 3533.18846) (1466.81753 3536.95351) (1447.96380 3533.18224)))
("SF_PLANTING" 0 ((1447.96380 3476.62115) (1557.31527 3476.61493) (1579.93971 3472.85068) (1704.37410 3476.62115)))
("SF_ARCHITECTURE" 0 ((1459.27602 5003.77115) (1451.74106 4981.14672) (1455.49876 4954.75113) (1451.73450 4920.81448)
(1455.49876 4796.38009) (1451.74106 4777.52681) (1451.72794 4147.81256) (1447.96380 4125.18812) (1448.11188 4046.00328)
(1451.73450 4034.69038)))
("SF_PLANTING" 0 ((1485.67115 4053.54491) (1466.81097 4035.89514) (1451.73450 4034.69038)))
("SF_PLANTING" 0 ((1704.37410 3401.20667) (1636.50079 3401.20667) (1613.87636 3401.20667) (1451.73450 3401.20667)))
("SF_PLANTING" 0 ((1451.73450 3367.27025) (1451.73450 3401.20667)))
("SF_PLANTING" 0 ((1451.73450 1210.40724) (1451.73450 1236.80147)))
("SF_ARCHITECTURE" 0 ((2262.44344 1349.92364) (2254.90826 1387.63292) (2258.66640 1414.02715) (2258.67296 2126.69683)
(2253.69740 2183.25170) (2198.34061 2216.14514) (2111.61414 2257.61652) (2002.26244 2291.55317) (1938.15962 2303.77410)
(1885.36957 2304.06957) (1874.05735 2307.54457) (1772.24740 2303.77410) (1700.60328 2291.55939) (1595.02262 2257.62342)
(1500.75419 2212.23303) (1455.86731 2184.08710) (1451.73450 2164.40396) (1451.73450 1304.67477) (1455.50532 1255.65611)
(1451.73450 1236.80147)))
("SF_PLANTING" 0 ((1451.73450 1210.40724) (1455.50532 1195.32523)))
("SF_PLANTING" 0 ((1455.50532 1195.32523) (1489.44197 1195.32523)))
("SF_PLANTING" 0 ((1455.50532 1161.38857) (1455.50532 1195.32523)))
("SF_PLANTING" 0 ((1485.67115 1161.38857) (1455.50532 1161.38857)))
("SF_PLANTING" 0 ((1455.50532 1161.38857) (1455.50532 1112.36708)))
("SF_PLANTING" 0 ((1463.04672 1112.36708) (1455.50532 1112.36708)))
("SF_ARCHITECTURE" 0 ((1459.27602 5030.16550) (1474.35894 5030.16550)))
("SF_ARCHITECTURE" 0 ((1459.27602 5003.77115) (1500.75407 5020.05113) (1508.29559 5033.93665)))
("SF_PLANTING" 0 ((1463.04672 1112.36708) (1463.04672 1101.05486) (1459.27602 1097.28507)))
("SF_PLANTING" 0 ((1523.37862 3763.19717) (1518.40351 3789.58654) (1474.51357 3827.30057) (1463.04672 3855.58111)))
("SF_PLANTING" 0 ((1463.04672 3855.58111) (1466.81753 3883.86165)))
("SF_PLANTING" 0 ((1463.04672 3855.58111) (1474.35905 3861.08541) (1508.28903 3864.11256) (1530.92002 3891.40271)))
("SF_PLANTING" 0 ((1496.98337 1131.22172) (1489.43529 1117.34310) (1463.04672 1112.36708)))
("SF_PLANTING" 0 ((1500.75419 4162.89593) (1485.67115 4161.83925) (1470.58824 4151.58371)))
("SF_PLANTING" 0 ((1519.60781 3917.79830) (1474.35894 3932.88043)))
("SF_PLANTING" 0 ((1478.12975 3974.35939) (1474.35894 3932.88043)))
("SF_PLANTING" 0 ((1478.12975 3974.35939) (1493.21267 3974.50724) (1512.06640 3981.90045)))
("SF_PLANTING" 0 ((1485.67115 3691.55396) (1481.90045 3684.01165)))
("SF_PLANTING" 0 ((1644.04219 3619.90950) (1598.79333 3620.05758) (1583.71041 3623.66753) (1564.85667 3619.91572)
(1481.90045 3619.90950)))
("SF_ARCHITECTURE" 0 ((1485.67115 5041.47771) (1500.75407 5040.42229) (1508.29559 5033.93665)))
("SF_PLANTING" 0 ((1485.67115 3653.84615) (1542.23224 3653.69808) (1557.31527 3650.08190) (1587.48111 3653.54966)
(1610.10554 3650.07500)))
("SF_PLANTING" 0 ((1647.81301 3589.74333) (1621.41776 3582.20860) (1591.25192 3585.96663) (1485.67115 3585.97285)))
("SF_PLANTING" 0 ((1496.98337 1131.22172) (1485.67115 1161.38857)))
("SF_PLANTING" 0 ((1485.67115 1161.38857) (1489.29389 1168.93575) (1489.44197 1195.32523)))
("SF_PLANTING" 0 ((1500.75419 1233.03167) (1489.44197 1195.32523)))
("SF_PLANTING" 0 ((1493.21267 1312.21719) (1500.75419 1312.21719)))
("SF_PLANTING" 0 ((1549.77376 1138.76414) (1496.98337 1131.22172)))
("SF_PLANTING" 0 ((1496.98337 889.89446) (2028.65735 889.89446) (2047.51131 889.89446)))
("SF_PLANTING" 0 ((1500.75419 4162.89593) (1508.29559 4151.58371) (1508.29559 4076.16934) (1508.29559 4064.85713)))
("SF_ARCHITECTURE" 0 ((1500.75419 4162.89593) (1496.98993 4215.68586) (1496.98337 4513.57466) (1500.74762 4536.19910)
(1508.29559 4969.82760) (1564.85667 5010.12081) (1610.10554 5032.74525) (1677.97885 5059.27590) (1745.85215 5075.26652)
(1809.94819 5082.80170) (1816.29197 5079.03088) (1817.49627 4074.28314)))
("SF_PLANTING" 0 ((1715.68631 3371.04072) (1704.37398 3367.27647) (1512.06640 3367.26403) (1500.75419 3363.49898)))
("SF_ARCHITECTURE" 0 ((1500.75419 2141.77952) (1500.75419 1312.21719)))
("SF_ARCHITECTURE" 0 ((1500.75419 2141.77952) (1490.65283 2153.09174) (1490.65283 2160.63348) (1504.52489 2174.65984)
(1519.60781 2179.48744)))
("SF_ARCHITECTURE" 0 ((1500.75419 2141.77952) (1526.99468 2160.77500) (1530.92002 2168.17523)))
("SF_PLANTING" 0 ((1500.75419 1312.21719) (1504.22885 1297.13518) (1496.98337 1259.42590) (1500.75419 1233.03167)))
("SF_PLANTING" 0 ((1549.77376 1248.11369) (1515.83710 1234.08111) (1500.75419 1233.03167)))
("SF_PLANTING" 0 ((1553.54446 1029.41176) (1512.07296 1029.55950) (1504.52489 1033.18156)))
("SF_PLANTING" 0 ((1504.52489 1033.18156) (1520.66414 1074.65441) (1538.46154 1085.82443) (1552.34016 1082.04774)
(1553.54446 1036.95419)))
("SF_ARCHITECTURE" 0 ((1508.29559 5049.02002) (1519.61437 5052.63597) (1530.92002 5049.02002)))
("SF_ARCHITECTURE" 0 ((1530.92002 5049.02002) (1526.99468 5037.86176) (1508.29559 5033.93665)))
("SF_PLANTING" 0 ((1508.29559 4064.85713) (1508.44367 3993.21267) (1512.06640 3981.90045)))
("SF_PLANTING" 0 ((1572.39819 4053.54491) (1586.28337 4061.24061) (1597.73688 4091.25147) (1594.86776 4101.35984)
(1579.93971 4101.50758) (1534.69084 4069.83179) (1508.29559 4064.85713)))
("SF_PLANTING" 0 ((1519.60781 3981.90045) (1512.06640 3981.90045)))
("SF_PLANTING" 0 ((1519.60781 3981.90045) (1527.14932 3981.90045)))
("SF_PLANTING" 0 ((1519.60781 3981.90045) (1519.60781 3978.12930) (1527.14932 3974.35939)))
("SF_PLANTING" 0 ((1519.60781 3917.79830) (1520.81210 3910.25600) (1530.92002 3902.71493)))
("SF_PLANTING" 0 ((1519.60781 3917.79830) (1519.75588 3951.73495) (1527.14932 3974.35939)))
("SF_ARCHITECTURE" 0 ((1519.60781 2179.48744) (1530.92002 2168.17523)))
("SF_ARCHITECTURE" 0 ((1519.60781 2179.48744) (1530.92002 2189.59548) (1542.23224 2190.79966)))
("SF_PLANTING" 0 ((1523.37862 3763.19717) (1530.92002 3759.42726)))
("SF_PLANTING" 0 ((1527.14932 3974.35939) (1527.14932 3981.90045)))
("SF_PLANTING" 0 ((1610.10554 4019.60826) (1598.79333 4022.18088) (1576.16889 4017.04129) (1561.08597 4023.22421)
(1553.54457 4022.17432) (1543.42998 4012.06595) (1537.26380 3993.21267) (1527.14932 3981.90045)))
("SF_PLANTING" 0 ((1572.39819 3966.81708) (1549.77376 3974.21097) (1527.14932 3974.35939)))
("SF_PLANTING" 0 ((1530.92002 3759.42726) (1527.14932 3721.71946)))
("SF_ARCHITECTURE" 0 ((2254.90192 4174.20814) (2254.90192 4193.06143) (2254.90192 4313.72590) (2254.90192 4336.35034)
(2254.90192 4377.82805) (2254.90192 4457.01357) (2254.90192 4479.63801) (2254.90192 4536.19910) (2254.90192 4551.28247)
(2254.90192 4792.60894) (2254.90192 4811.46346) (2254.90192 4905.73111) (2254.90192 4920.81448) (2254.74729 5003.77048)
(2250.97636 5011.16414) (2194.57014 5044.34061) (2096.53066 5089.44174) (1979.63801 5124.28631) (1896.68201 5135.59853)
(1817.49627 5135.59853) (1734.53993 5124.28631) (1685.52036 5112.07240) (1621.41776 5089.44796) (1542.23235 5050.21731)
(1530.92002 5049.02002)))
("SF_PLANTING" 0 ((1530.92002 3902.71493) (1530.92002 3891.40271)))
("SF_PLANTING" 0 ((1530.92002 3902.71493) (1572.39819 3944.19265)))
("SF_PLANTING" 0 ((1598.79333 3868.77828) (1594.86799 3875.12862) (1583.71041 3879.04072) (1542.23235 3884.01561)
(1530.92002 3891.40271)))
("SF_PLANTING" 0 ((1934.38914 3763.19717) (1885.36957 3766.96833) (1610.10554 3763.20407) (1579.93971 3766.96210)
(1530.92002 3759.42726)))
("SF_ARCHITECTURE" 0 ((1553.54446 2179.48744) (1545.99638 2171.05090) (1530.92002 2168.17523)))
("SF_PLANTING" 0 ((1546.00305 1346.15385) (1532.12432 1331.07670) (1530.92002 1323.52941)))
("SF_PLANTING" 0 ((1595.02262 3849.92500) (1564.85667 3839.50769) (1534.69084 3819.75826)))
("SF_PLANTING" 0 ((1568.62749 1217.94966) (1548.72410 1191.70102) (1534.69084 1184.01301)))
("SF_ARCHITECTURE" 0 ((1553.54446 2179.48744) (1542.23224 2190.79966)))
("SF_ARCHITECTURE" 0 ((1542.23224 2190.79966) (1553.54457 2200.90769) (1561.08597 2201.95724) (1572.24355 2197.29118)
(1576.16889 2190.79966)))
("SF_PLANTING" 0 ((1549.77376 1248.11369) (1564.85667 1244.34389)))
("SF_PLANTING" 0 ((1553.54446 1266.96833) (1549.77376 1248.11369)))
("SF_PLANTING" 0 ((1549.77376 1138.76414) (1564.85667 1127.59966) (1617.64706 1119.90950)))
("SF_PLANTING" 0 ((1549.77376 1138.76414) (1568.62749 1160.33145) (1606.33484 1172.70079)))
("SF_ARCHITECTURE" 0 ((1621.41776 4400.45249) (1603.61380 4377.82805) (1586.28993 4340.12025) (1553.54446 4287.33032)))
("SF_ARCHITECTURE" 0 ((1553.54446 2179.48744) (1568.62081 2182.36312) (1576.16889 2190.79966)))
("SF_PLANTING" 0 ((1561.08597 1036.95419) (1553.54446 1036.95419)))
("SF_PLANTING" 0 ((1553.54446 1029.41176) (1553.54446 1036.95419)))
("SF_PLANTING" 0 ((1553.54446 1029.41176) (1576.16889 1018.24796) (1606.32828 1018.24729) (1613.87636 1021.86934)))
("SF_ARCHITECTURE" 0 ((1557.31527 5199.84876) (1564.85667 5192.30769)))
("SF_ARCHITECTURE" 0 ((1557.31527 5199.84876) (1564.86335 5209.95713) (1583.71041 5211.16097)))
("SF_ARCHITECTURE" 0 ((1557.31527 1478.13066) (1586.28337 1523.37952) (1599.99106 1553.54355) (1613.87636 1568.62839)))
("SF_PLANTING" 0 ((1572.39819 1361.23586) (1576.01425 1338.61143) (1561.08597 1300.90498)))
("SF_PLANTING" 0 ((1568.62749 1217.94966) (1564.85667 1244.34389)))
("SF_PLANTING" 0 ((1568.62749 1217.94966) (1591.25192 1222.92432) (1602.40950 1233.03167) (1616.29468 1278.12590)
(1602.56414 1281.90260) (1591.39989 1277.22421) (1564.85667 1244.34389)))
("SF_PLANTING" 0 ((1572.39819 3966.81708) (1572.39819 3944.19265)))
("SF_PLANTING" 0 ((1572.39819 3966.81708) (1610.10554 3989.44152)))
("SF_PLANTING" 0 ((1572.39819 3944.19265) (1587.48111 3944.19265)))
("SF_PLANTING" 0 ((1644.04219 3693.43891) (1621.41776 3695.16991) (1591.25192 3691.39898) (1572.39819 3684.01165)))
("SF_ARCHITECTURE" 0 ((1576.16889 2213.42410) (1591.25192 2213.42410)))
("SF_ARCHITECTURE" 0 ((1598.79333 2202.11188) (1576.16889 2190.79966)))
("SF_ARCHITECTURE" 0 ((1583.71041 5211.16097) (1591.25192 5203.61991)))
("SF_ARCHITECTURE" 0 ((1583.71041 5211.16097) (1591.25848 5221.26934) (1628.95928 5231.07093) (1681.74966 5251.58326)
(1730.76923 5263.80373) (1772.24740 5267.72206)))
("SF_PLANTING" 0 ((1613.87636 3883.86165) (1612.67206 3910.25600) (1592.30814 3932.88043) (1587.48111 3944.19265)))
("SF_PLANTING" 0 ((1587.48111 3944.19265) (1598.79333 3951.73495)))
("SF_ARCHITECTURE" 0 ((1591.25192 2213.42410) (1598.79333 2202.11188)))
("SF_ARCHITECTURE" 0 ((1621.41776 2217.19457) (1617.49242 2223.53835) (1606.33484 2224.58167) (1591.25192 2213.42410)))
("SF_PLANTING" 0 ((1621.41776 1101.05486) (1591.25192 1074.66063)))
("SF_PLANTING" 0 ((1595.02262 3804.67613) (1605.13054 3808.60102) (1605.27862 3831.07048) (1595.02262 3849.92500)))
("SF_PLANTING" 0 ((1598.79333 3868.77828) (1595.02262 3849.92500)))
("SF_PLANTING" 0 ((1598.79333 3868.77828) (1606.33484 3868.77828)))
("SF_ARCHITECTURE" 0 ((1621.41776 2217.19457) (1617.49242 2207.08654) (1598.79333 2202.11188)))
("SF_PLANTING" 0 ((1681.74966 3880.09050) (1676.77455 3857.46606) (1666.66663 3847.50577) (1625.18857 3854.75158)
(1606.33484 3868.77828)))
("SF_PLANTING" 0 ((1613.87636 3883.86165) (1606.33484 3868.77828)))
("SF_ARCHITECTURE" 0 ((1685.52036 1791.10011) (1680.55192 1776.01810) (1646.75679 1719.45701) (1606.33484 1670.43835)))
("SF_PLANTING" 0 ((1621.41776 1150.07636) (1606.33484 1172.70079)))
("SF_PLANTING" 0 ((1704.37410 1146.30373) (1699.55362 1172.70079) (1680.69344 1202.85995) (1670.43733 1210.24502)
(1651.58371 1205.43880) (1640.27149 1196.52862) (1614.02443 1190.35543) (1606.33484 1172.70079)))
("SF_PLANTING" 0 ((1610.10554 4019.60826) (1610.10554 3989.44152)))
("SF_PLANTING" 0 ((1610.10554 4019.60826) (1651.42907 4022.17432) (1654.15011 4008.30226) (1644.04219 4000.75373)))
("SF_PLANTING" 0 ((1610.10554 3989.44152) (1625.04050 3984.61493) (1647.96753 3948.11844) (1670.43744 3936.65158)))
("SF_PLANTING" 0 ((1613.87636 1021.86934) (1610.10554 1048.26640)))
("SF_PLANTING" 0 ((1613.87636 3883.86165) (1651.58371 3884.00950) (1670.43744 3891.40271)))
("SF_PLANTING" 0 ((1613.87636 1021.86934) (1644.04219 1018.24729) (1666.66663 1029.41176)))
("SF_ARCHITECTURE" 0 ((1760.93518 4709.65351) (1750.67907 4698.34061) (1710.85928 4630.61584) (1694.25962 4619.00735)
(1657.92749 4555.20079) (1645.09197 4543.73394) (1617.64706 4502.26244)))
("SF_PLANTING" 0 ((1621.41776 1101.05486) (1617.64706 1119.90950)))
("SF_PLANTING" 0 ((1617.64706 1119.90950) (1621.26968 1127.45679) (1621.41776 1150.07636)))
("SF_ARCHITECTURE" 0 ((1621.41776 4400.45249) (1632.72998 4423.07692)))
("SF_ARCHITECTURE" 0 ((1621.41776 4400.45249) (1636.34615 4405.27975) (1644.04219 4423.07692)))
("SF_ARCHITECTURE" 0 ((1821.26697 1248.11369) (1817.34163 2247.35385) (1809.94819 2254.74706) (1708.14480 2247.21222)
(1662.89593 2234.99898) (1621.41776 2217.19457)))
("SF_ARCHITECTURE" 0 ((1621.41776 1595.02262) (1628.95928 1583.71041)))
("SF_PLANTING" 0 ((1674.20814 1116.13971) (1655.34785 1145.24808) (1644.04219 1149.92794) (1621.41776 1150.07636)))
("SF_PLANTING" 0 ((1621.41776 1101.05486) (1647.81301 1097.28507)))
("SF_ARCHITECTURE" 0 ((1632.72998 1572.39819) (1628.95928 1583.71041)))
("SF_ARCHITECTURE" 0 ((1628.95928 1583.71041) (1639.06719 1591.25769) (1640.27149 1602.56505)))
("SF_ARCHITECTURE" 0 ((1644.04219 4423.07692) (1632.72998 4423.07692)))
("SF_ARCHITECTURE" 0 ((1636.50079 4438.16029) (1632.72998 4434.38914) (1632.72998 4423.07692)))
("SF_ARCHITECTURE" 0 ((1632.72998 1613.87726) (1640.27149 1602.56505)))
("SF_ARCHITECTURE" 0 ((1651.58371 1621.41686) (1650.37941 1610.11222) (1640.27149 1602.56505)))
("SF_ARCHITECTURE" 0 ((1655.35441 4441.93020) (1650.39253 4427.00204) (1644.04219 4423.07692)))
("SF_PLANTING" 0 ((1644.04219 3693.43891) (1644.04219 3717.94830)))
("SF_PLANTING" 0 ((1644.04219 3693.43891) (1644.04219 3680.24174)))
("SF_PLANTING" 0 ((1644.04219 3693.43891) (1685.52036 3695.31765) (1704.37410 3691.56708) (1753.39367 3695.31765)
(1768.47658 3691.55396)))
("SF_PLANTING" 0 ((1644.04219 3619.90950) (1738.31075 3619.90950)))
("SF_PLANTING" 0 ((1738.31075 3650.07500) (1647.96765 3648.87115) (1644.19683 3642.52771) (1644.04219 3619.90950)))
("SF_ARCHITECTURE" 0 ((1651.58371 1621.41686) (1644.04219 1632.72907)))
("SF_PLANTING" 0 ((1666.66663 1029.41176) (1647.81301 1097.28507)))
("SF_PLANTING" 0 ((1674.20814 1116.13971) (1647.81301 1097.28507)))
("SF_ARCHITECTURE" 0 ((1666.66663 1651.58371) (1665.46233 1632.72907) (1651.58371 1621.41686)))
("SF_ARCHITECTURE" 0 ((1666.66663 4460.78473) (1655.35441 4468.32579)))
("SF_ARCHITECTURE" 0 ((1655.35441 4441.93020) (1644.34491 4453.24310) (1648.86267 4464.40068) (1655.35441 4468.32579)))
("SF_ARCHITECTURE" 0 ((1659.12523 4483.40916) (1655.35441 4479.63801) (1655.35441 4468.32579)))
("SF_ARCHITECTURE" 0 ((1655.35441 4441.93020) (1665.46233 4453.23620) (1666.66663 4460.78473)))
("SF_PLANTING" 0 ((1666.66663 3585.97285) (1659.12523 3585.97285)))
("SF_ARCHITECTURE" 0 ((1666.66663 1651.58371) (1659.12523 1651.58371)))
("SF_ARCHITECTURE" 0 ((1666.66663 4460.78473) (1708.14480 4521.11572)))
("SF_ARCHITECTURE" 0 ((1666.66663 1651.58371) (1684.47070 1666.81414) (1699.40554 1689.29016) (1704.37410 1704.37500)))
("SF_PLANTING" 0 ((1708.14480 1029.41176) (1666.66663 1029.41176)))
("SF_PLANTING" 0 ((1677.97885 3936.65158) (1670.43744 3936.65158)))
("SF_PLANTING" 0 ((1670.43744 3936.65158) (1670.43744 3891.40271)))
("SF_PLANTING" 0 ((1681.74966 3880.09050) (1670.43744 3891.40271)))
("SF_PLANTING" 0 ((1674.20814 1116.13971) (1685.52036 1116.13971)))
("SF_PLANTING" 0 ((1677.97885 3936.65158) (1682.94740 3970.58824) (1696.98066 3993.21267) (1719.45701 4011.00984)
(1734.53337 4011.91810) (1742.08145 4008.29604)))
("SF_PLANTING" 0 ((1677.97885 3936.65158) (1734.53993 3940.42274)))
("SF_PLANTING" 0 ((1681.74966 3880.09050) (1749.62296 3883.86165)))
("SF_ARCHITECTURE" 0 ((1685.52036 1791.10011) (1689.29106 1791.10011) (1693.06188 1798.64253)))
("SF_ARCHITECTURE" 0 ((1685.52036 1791.10011) (1685.52036 1794.87274) (1693.06188 1798.64253)))
("SF_PLANTING" 0 ((1704.37410 1093.51527) (1685.52036 1116.13971)))
("SF_PLANTING" 0 ((1704.37410 1146.30373) (1703.16980 1134.99152) (1685.52036 1116.13971)))
("SF_ARCHITECTURE" 0 ((1696.83258 1806.18495) (1689.29106 1817.49717)))
("SF_ARCHITECTURE" 0 ((1696.83258 1806.18495) (1693.06188 1798.64253)))
("SF_ARCHITECTURE" 0 ((1696.83258 1806.18495) (1711.76742 1817.49717) (1757.16437 1885.36980)))
("SF_PLANTING" 0 ((1704.37410 3533.18224) (1768.47658 3533.18224)))
("SF_PLANTING" 0 ((1704.37410 3533.18224) (1700.75792 3514.32907) (1704.37410 3476.62115)))
("SF_PLANTING" 0 ((1704.37410 3533.18224) (1704.52217 3574.65373) (1708.14480 3582.20238)))
("SF_PLANTING" 0 ((1809.95475 3472.85068) (1715.68631 3472.85690) (1704.37410 3476.62115)))
("SF_PLANTING" 0 ((1704.37410 3401.20667) (1772.24740 3401.20667) (1813.72545 3401.20667)))
("SF_PLANTING" 0 ((1711.91550 3435.14333) (1704.52873 3427.59491) (1704.37410 3401.20667)))
("SF_PLANTING" 0 ((1749.62296 1153.84615) (1726.99853 1146.45215) (1704.37410 1146.30373)))
("SF_PLANTING" 0 ((1704.37410 1093.51527) (1704.37410 1078.43043)))
("SF_PLANTING" 0 ((1743.96686 1095.39876) (1704.37410 1093.51527)))
("SF_PLANTING" 0 ((1708.14480 1029.41176) (1719.45701 1022.02466) (1760.93518 1022.01776) (1776.01810 1025.64197)))
("SF_PLANTING" 0 ((1742.08145 1070.89084) (1719.60509 1055.65894) (1708.14480 1029.41176)))
("SF_PLANTING" 0 ((1753.39367 3921.56821) (1734.53993 3940.42274)))
("SF_PLANTING" 0 ((1734.53993 3940.42274) (1735.74423 3951.72805) (1742.08801 3958.07149) (1764.70588 3959.27602)))
("SF_PLANTING" 0 ((1813.72545 3435.14333) (1802.41324 3435.14333) (1734.53993 3435.14333)))
("SF_PLANTING" 0 ((1998.49197 3359.72851) (1953.24310 3367.26403) (1734.53993 3367.27025)))
("SF_PLANTING" 0 ((1742.08145 1070.89084) (1753.23914 1063.34152) (1774.81380 1033.18914) (1776.01810 1025.64197)))
("SF_PLANTING" 0 ((1743.96686 1095.39876) (1742.08145 1070.89084)))
("SF_PLANTING" 0 ((1743.96686 1095.39876) (1794.87183 1093.51527)))
("SF_PLANTING" 0 ((1743.96686 1095.39876) (1753.39367 1116.13971)))
("SF_PLANTING" 0 ((1753.39367 3921.56821) (1749.62296 3883.86165)))
("SF_PLANTING" 0 ((1794.87183 3887.63156) (1783.55950 3884.00950) (1749.62296 3883.86165)))
("SF_PLANTING" 0 ((1749.62296 1153.84615) (1749.62296 1184.01301)))
("SF_PLANTING" 0 ((1776.01810 1248.11369) (1767.27885 1274.50317) (1760.92851 1280.84695) (1749.62296 1280.84695)
(1735.74423 1266.96833) (1730.92387 1248.11369) (1734.68801 1210.40724) (1743.13111 1187.93744) (1749.62296
1184.01301)))
("SF_PLANTING" 0 ((1783.55962 1168.92817) (1772.24072 1186.57794) (1757.17104 1187.63507) (1749.62296 1184.01301)))
("SF_PLANTING" 0 ((1779.78880 1153.84615) (1749.62296 1153.84615)))
("SF_PLANTING" 0 ((1794.87183 3917.79830) (1753.39367 3921.56821)))
("SF_PLANTING" 0 ((1753.39367 592.00509) (1772.24740 592.00509)))
("SF_PLANTING" 0 ((1768.47658 3650.07500) (1757.16437 3650.07500)))
("SF_ARCHITECTURE" 0 ((1772.24740 5267.72206) (1768.32195 5316.73586) (1760.93518 5324.28314)))
("SF_ARCHITECTURE" 0 ((1919.30645 5328.05430) (1930.47036 5407.23982) (1930.46380 5433.63473) (1926.69299 5441.02183)
(1915.53518 5444.94072) (1760.93518 5443.74287) (1750.97534 5433.63473) (1760.93518 5324.28314)))
("SF_ARCHITECTURE" 0 ((1772.24740 2450.98066) (1768.32206 2492.45826) (1760.93518 2503.77048)))
("SF_ARCHITECTURE" 0 ((1760.93518 2503.77048) (1764.55781 2522.62443) (1757.31244 2552.79061) (1750.82726 2616.89265)
(1760.94174 2630.77195) (1911.76471 2631.96923) (1923.07036 2628.05023) (1930.46380 2613.12217) (1915.53518
2503.77048)))
("SF_PLANTING" 0 ((1768.47658 4083.71041) (1768.47658 4076.16934)))
("SF_PLANTING" 0 ((1817.49627 4074.28314) (1783.55962 4072.54627) (1768.47658 4076.16934)))
("SF_PLANTING" 0 ((1813.72545 3981.90045) (1791.10769 3982.05509) (1784.75735 3985.82557) (1779.93688 4000.75373)
(1778.58450 4030.91357) (1754.59819 4046.00950) (1754.45000 4057.31482) (1768.47658 4076.16934)))
("SF_PLANTING" 0 ((1768.47658 3721.71946) (1772.09276 3710.40724) (1768.47658 3691.55396)))
("SF_PLANTING" 0 ((1768.47658 3650.07500) (1768.47658 3691.55396)))
("SF_PLANTING" 0 ((1953.24310 3699.09502) (1945.69480 3695.47229) (1768.47658 3691.55396)))
("SF_PLANTING" 0 ((1768.47658 3650.07500) (1783.55962 3650.07500)))
("SF_PLANTING" 0 ((1768.47658 3619.90950) (1934.38258 3623.82851) (1941.93088 3627.45057)))
("SF_PLANTING" 0 ((1768.47658 3533.18224) (1764.86052 3570.89016) (1768.47658 3582.20238)))
("SF_PLANTING" 0 ((1768.47658 3533.18224) (1847.66210 3533.18846) (1870.28654 3536.95351) (1994.72070 3533.18846)
(2017.34514 3536.95351)))
("SF_ARCHITECTURE" 0 ((1772.24740 5267.72206) (1783.55962 5256.56482) (1892.91075 5256.41674) (1904.07511 5260.33563)
(1911.76471 5271.49321)))
("SF_ARCHITECTURE" 0 ((1907.99423 2450.98066) (1900.44593 2436.05181) (1885.36957 2432.12670) (1791.10102 2432.28133)
(1783.56618 2436.05181) (1772.24740 2450.98066)))
("SF_PLANTING" 0 ((1776.01810 1248.11369) (1769.68088 1236.80905) (1772.24740 1229.26188)))
("SF_PLANTING" 0 ((1776.01810 3842.38269) (1798.64253 3846.00577) (1825.03767 3838.61278)))
("SF_PLANTING" 0 ((1821.26697 1248.11369) (1776.01810 1248.11369)))
("SF_PLANTING" 0 ((1821.26697 1025.64197) (1776.01810 1025.64197)))
("SF_PLANTING" 0 ((1779.78880 1153.84615) (1784.61584 1112.36708) (1794.87183 1093.51527)))
("SF_PLANTING" 0 ((1783.55962 1168.92817) (1779.78880 1153.84615)))
("SF_PLANTING" 0 ((1783.55962 1168.92817) (1821.26697 1168.92817)))
("SF_PLANTING" 0 ((1794.87183 592.00509) (1783.55962 592.00509)))
("SF_PLANTING" 0 ((1794.87183 3917.79830) (1794.87183 3887.63156)))
("SF_PLANTING" 0 ((1794.87183 3917.79830) (1834.46459 3934.76663)))
("SF_PLANTING" 0 ((1794.87183 3887.63156) (1836.34989 3887.63156)))
("SF_PLANTING" 0 ((1821.26697 1093.51527) (1794.87183 1093.51527)))
("SF_PLANTING" 0 ((1798.64253 3650.07500) (1809.95475 3653.83993) (1926.84740 3653.84615)))
("SF_PLANTING" 0 ((1806.18405 3465.30894) (1809.95475 3472.85068)))
("SF_PLANTING" 0 ((1832.57919 3593.51459) (1809.95475 3585.97285)))
("SF_PLANTING" 0 ((1809.95475 3472.85068) (1972.09627 3472.85690) (1998.49197 3476.62115)))
("SF_PLANTING" 0 ((1834.46459 3934.76663) (1822.32330 3951.73495) (1813.72545 3981.90045)))
("SF_PLANTING" 0 ((1817.49627 4074.28314) (1817.34819 3989.44842) (1813.72545 3981.90045)))
("SF_PLANTING" 0 ((1979.63801 3431.37229) (1926.84740 3435.13043) (1907.99423 3431.37851) (1813.72545 3435.14333)))
("SF_PLANTING" 0 ((1813.72545 3435.14333) (1813.72545 3401.20667)))
("SF_PLANTING" 0 ((1983.40848 3401.20667) (1968.32579 3401.20667) (1813.72545 3401.20667)))
("SF_PLANTING" 0 ((1817.49627 4074.28314) (1847.51414 4080.09423) (1857.77658 4095.02262) (1858.97432 4106.33484)))
("SF_PLANTING" 0 ((1821.26697 1248.11369) (1821.26697 1168.92817)))
("SF_PLANTING" 0 ((1821.26697 1093.51527) (1821.26697 1157.61595) (1821.26697 1168.92817)))
("SF_PLANTING" 0 ((1821.26697 1093.51527) (1828.80848 1093.51527)))
("SF_PLANTING" 0 ((1881.59876 1029.41176) (1862.74514 1018.25419) (1828.81505 1018.25419) (1821.26697 1025.64197)))
("SF_PLANTING" 0 ((1828.80848 1093.51527) (1821.26697 1025.64197)))
("SF_PLANTING" 0 ((1825.03767 3838.61278) (1826.24197 3808.60102) (1832.58575 3804.83710) (1843.89140 3808.44604)))
("SF_PLANTING" 0 ((1825.03767 3838.61278) (1843.89140 3846.15385)))
("SF_PLANTING" 0 ((1877.82805 1101.05486) (1862.74514 1093.66301) (1828.80848 1093.51527)))
("SF_PLANTING" 0 ((1834.46459 3934.76663) (1836.34989 3887.63156)))
("SF_PLANTING" 0 ((1834.46459 3934.76663) (1847.65894 3940.27093) (1913.65034 3944.19265)))
("SF_PLANTING" 0 ((1843.89140 3883.86165) (1836.34989 3887.63156)))
("SF_PLANTING" 0 ((1900.45249 592.00509) (1840.12070 592.00509)))
("SF_PLANTING" 0 ((1900.45249 3985.67161) (1862.75170 3990.64627) (1843.89140 4023.37817)))
("SF_PLANTING" 0 ((1843.89140 3883.86165) (1874.05735 3882.80498) (1891.02590 3870.66324)))
("SF_PLANTING" 0 ((1843.89140 3883.86165) (1843.89140 3846.15385)))
("SF_PLANTING" 0 ((1891.02590 3870.66324) (1866.51584 3847.35837) (1843.89140 3846.15385)))
("SF_PLANTING" 0 ((1843.89140 3593.51459) (1862.74514 3589.75645) (1877.82805 3593.35995) (1896.68201 3589.75645)
(1926.84740 3593.50837) (1945.70136 3589.74333)))
("SF_PLANTING" 0 ((1847.66210 1165.15837) (1851.43292 1172.70079)))
("SF_PLANTING" 0 ((1851.43292 1259.42590) (1855.20362 1244.34389)))
("SF_PLANTING" 0 ((1885.36957 1168.92817) (1851.43292 1172.70079)))
("SF_PLANTING" 0 ((1855.20362 1244.34389) (1847.81018 1229.26188) (1847.81018 1184.01301) (1851.43292 1172.70079)))
("SF_PLANTING" 0 ((1855.20362 4053.54491) (1855.20362 4061.08597)))
("SF_PLANTING" 0 ((1892.91097 1244.34389) (1855.20362 1244.34389)))
("SF_PLANTING" 0 ((1874.05735 3276.77229) (1923.07692 3276.77229) (1945.70136 3299.39695)))
("SF_PLANTING" 0 ((1889.14027 1101.05486) (1877.82805 1101.05486)))
("SF_PLANTING" 0 ((1877.82805 1101.05486) (1885.22149 1138.76414) (1885.36957 1168.92817)))
("SF_PLANTING" 0 ((1911.76471 1025.64197) (1881.59876 1029.41176)))
("SF_PLANTING" 0 ((1889.14027 1101.05486) (1881.59876 1029.41176)))
("SF_PLANTING" 0 ((1892.91097 1180.24038) (1885.36957 1168.92817)))
("SF_PLANTING" 0 ((1889.14027 1101.05486) (1907.99423 1101.05486)))
("SF_PLANTING" 0 ((1891.02590 3870.66324) (1900.38495 3865.22941) (1938.15962 3865.00713)))
("SF_PLANTING" 0 ((1891.02590 3870.66324) (1899.25124 3883.85792) (1900.60079 3902.71493) (1914.40509 3936.64536)
(1913.65034 3944.19265)))
("SF_PLANTING" 0 ((1892.91097 1244.34389) (1892.91097 1251.88631)))
("SF_ARCHITECTURE" 0 ((2209.65283 1308.44740) (2205.88235 1892.91075) (2205.88235 1915.53518) (2208.44853 2149.32127)
(2194.57014 2163.34762) (2160.63348 2182.20848) (2051.28179 2231.22093) (1987.17975 2247.21301) (1904.22330 2254.74706)
(1892.91097 2250.97658) (1892.91097 2239.81900) (1892.91097 1251.88631)))
("SF_PLANTING" 0 ((1926.84740 1255.65611) (1892.91097 1251.88631)))
("SF_PLANTING" 0 ((1892.91097 1244.34389) (1892.91097 1180.24038)))
("SF_PLANTING" 0 ((1892.91097 1180.24038) (1900.45249 1180.24038) (1904.22296 1184.01301)))
("SF_PLANTING" 0 ((1900.45249 3985.67161) (1900.45249 3996.98382)))
("SF_ARCHITECTURE" 0 ((1900.45249 3996.98382) (1893.06561 4008.29604) (1889.14683 4042.23269) (1892.90419 4061.08597)
(1894.11505 5071.64378) (1904.22330 5081.60351) (1987.17975 5071.49604) (2055.05305 5051.74072) (2171.94570 4998.80894)
(2198.34061 4983.86120) (2207.40566 4973.60441) (2209.64627 4166.66708) (2205.88235 4125.18812)))
("SF_PLANTING" 0 ((1972.09627 4023.37817) (1960.78405 4029.72885) (1945.70136 4031.66686) (1900.45249 3996.98382)))
("SF_PLANTING" 0 ((1900.45249 3985.67161) (1901.50848 3970.58824) (1913.65034 3944.19265)))
("SF_ARCHITECTURE" 0 ((1907.99423 2450.98066) (1919.30645 2447.35713) (1960.78405 2447.06165) (2043.74084 2427.29977)
(2092.76018 2406.78812) (2111.61414 2404.53382) (2213.42410 2351.89174) (2277.52613 2307.54457) (2322.77500 2267.26414)
(2341.62896 2255.95814) (2360.48292 2251.13122)))
("SF_ARCHITECTURE" 0 ((1907.99423 2450.98066) (1908.14208 2473.60509) (1915.53518 2503.77048)))
("SF_PLANTING" 0 ((1907.99423 1101.05486) (1923.97195 1078.43043) (1928.51912 1059.57862) (1925.64310 1044.49378)
(1911.76471 1025.64197)))
("SF_PLANTING" 0 ((1907.99423 1101.05486) (1926.84740 1108.59729)))
("SF_ARCHITECTURE" 0 ((2356.71165 5071.64446) (2322.77500 5084.01210) (2220.96505 5161.09174) (2119.15509 5217.65283)
(2009.80419 5255.36029) (1911.76471 5271.49321)))
("SF_ARCHITECTURE" 0 ((1919.30645 5328.05430) (1911.91301 5309.20102) (1909.19174 5282.80543) (1911.76471 5271.49321)))
("SF_PLANTING" 0 ((1911.76471 1025.64197) (1919.31301 1022.01776) (1960.78405 1022.01776) (1987.17975 1036.95419)))
("SF_PLANTING" 0 ((1923.07692 3944.19265) (1913.65034 3944.19265)))
("SF_ARCHITECTURE" 0 ((1915.53518 2503.77048) (1994.72070 2495.17930) (2077.67749 2472.54864) (2138.00905 2449.78959)
(2224.73631 2404.68224) (2281.29740 2366.97443) (2334.08722 2323.83145) (2360.48292 2311.46278)))
("SF_ARCHITECTURE" 0 ((2356.71165 5135.74661) (2337.85848 5140.71505) (2266.21391 5198.79333) (2145.55079 5266.53133)
(2088.98971 5289.29106) (2013.57466 5311.91550) (1919.30645 5328.05430)))
("SF_PLANTING" 0 ((1923.07692 3944.19265) (1941.93088 3929.26448) (1998.49197 3929.11052)))
("SF_PLANTING" 0 ((1923.07692 3944.19265) (1938.15962 3958.21934) (1960.78405 3966.81708)))
("SF_PLANTING" 0 ((1926.84740 1108.59729) (1931.81618 1142.52771) (1938.16652 1149.01923) (1953.24310 1153.84615)))
("SF_PLANTING" 0 ((1926.84740 1108.59729) (1964.55498 1117.33688) (1975.86753 1131.22172)))
("SF_PLANTING" 0 ((1934.38914 3763.19717) (1930.61867 3740.57274)))
("SF_PLANTING" 0 ((1941.93088 1199.09502) (1930.61867 1195.32523)))
("SF_PLANTING" 0 ((1934.38914 3763.19717) (1945.70136 3766.96833)))
("SF_PLANTING" 0 ((2006.03292 3865.00713) (1983.40848 3847.35837) (1972.09627 3846.15385) (1953.24310 3847.35837)
(1938.15962 3865.00713)))
("SF_PLANTING" 0 ((2006.03292 3865.00713) (1990.95023 3879.03382) (1979.63801 3883.70667) (1953.24310 3878.88597)
(1938.15962 3865.00713)))
("SF_ARCHITECTURE" 0 ((2039.96957 1602.56505) (2023.83088 1572.39819) (1999.54796 1546.00396) (1941.93088 1444.19400)))
("SF_PLANTING" 0 ((1960.78405 1187.78281) (1941.93088 1199.09502)))
("SF_PLANTING" 0 ((1957.01357 1225.48925) (1946.75735 1214.17704) (1941.93088 1199.09502)))
("SF_ARCHITECTURE" 0 ((1945.70136 4268.47704) (1954.29253 4291.10147) (1995.77715 4358.97477) (2020.05995 4385.36912)
(2036.19910 4419.30577)))
("SF_PLANTING" 0 ((2006.03292 3865.00713) (2005.88507 3823.52941) (2001.20645 3812.37183) (1972.09627 3807.24219)
(1957.16188 3796.08462) (1946.75735 3778.28054) (1945.70136 3766.96833)))
("SF_PLANTING" 0 ((1945.70136 3766.96833) (1994.72070 3770.73948)))
("SF_PLANTING" 0 ((2124.81120 3301.28179) (1945.70136 3299.39695)))
("SF_PLANTING" 0 ((1975.86753 1131.22172) (1953.24310 1153.84615)))
("SF_PLANTING" 0 ((1960.78405 1187.78281) (1953.24310 1153.84615)))
("SF_PLANTING" 0 ((1960.78405 1187.78281) (1998.49197 1200.15136) (2032.42862 1217.80124) (2043.74084 1216.75102)
(2062.59400 1206.63744)))
("SF_PLANTING" 0 ((2006.03292 1131.22172) (1975.86753 1131.22172)))
("SF_PLANTING" 0 ((2104.07240 3981.90045) (2100.14706 3993.20645) (2081.44796 4007.24559) (2017.34514 4035.88824)
(1994.72760 4056.11097) (1987.17975 4057.31482)))
("SF_PLANTING" 0 ((1987.17975 3963.04717) (2009.80419 3973.30271) (2039.96957 3978.12930)))
("SF_ARCHITECTURE" 0 ((1987.17975 1621.41686) (1993.67783 1625.34276) (2025.93631 1677.97794) (2050.23891 1708.14480)
(2082.49740 1764.70588) (2138.00905 1847.66188)))
("SF_PLANTING" 0 ((1998.49197 1036.95419) (1987.17975 1036.95419)))
("SF_PLANTING" 0 ((1987.17975 1036.95419) (1990.05520 1055.80600) (2013.72296 1088.53925) (2051.28179 1089.74265)))
("SF_ARCHITECTURE" 0 ((2141.77952 4668.17455) (2114.32862 4622.92568) (2078.86844 4577.67681) (2054.00317 4532.42794)
(2022.17240 4494.72138) (1994.72070 4453.24242)))
("SF_PLANTING" 0 ((2006.03292 3865.00713) (1998.49197 3929.11052)))
("SF_PLANTING" 0 ((2043.74084 3947.96380) (2017.34514 3934.07828) (1998.49197 3929.11052)))
("SF_PLANTING" 0 ((2107.84287 1025.64197) (2077.67749 1018.24729) (2017.34514 1018.25419) (2006.03982 1025.64683)
(1998.49197 1036.95419)))
("SF_PLANTING" 0 ((1998.49197 1036.95419) (2017.34514 1054.60260) (2039.96301 1059.73190) (2046.30701 1067.11821)
(2051.28179 1089.74265)))
("SF_PLANTING" 0 ((2017.34514 3593.51459) (2002.26244 3582.20238)))
("SF_PLANTING" 0 ((2006.03292 3865.00713) (2017.34514 3865.00713)))
("SF_PLANTING" 0 ((2047.51131 1131.22172) (2017.34548 1124.88416) (2006.03292 1131.22172)))
("SF_PLANTING" 0 ((2006.03292 1131.22172) (2021.11640 1149.92794) (2043.74084 1161.38857)))
("SF_PLANTING" 0 ((2051.28179 3672.69943) (2013.57466 3672.69943)))
("SF_PLANTING" 0 ((2017.34514 3593.51459) (2016.28914 3616.13903) (1998.78801 3646.30509) (2013.57466 3672.69943)))
("SF_PLANTING" 0 ((2013.57466 3672.69943) (2021.11640 3714.17839)))
("SF_PLANTING" 0 ((2073.90622 592.00509) (2013.57466 592.00509)))
("SF_PLANTING" 0 ((2096.53066 3853.69491) (2073.90622 3853.54706) (2039.96957 3846.30848) (2017.34514 3865.00713)))
("SF_PLANTING" 0 ((2126.69683 3906.48609) (2111.61414 3913.87251) (2081.44796 3909.06527) (2036.19910 3882.66380)
(2017.34514 3865.00713)))
("SF_PLANTING" 0 ((2017.34514 3593.51459) (2036.19910 3593.51459)))
("SF_PLANTING" 0 ((2111.61414 3770.73948) (2058.82353 3770.59106) (2036.20566 3765.76380) (2029.86165 3759.42036)
(2021.11640 3714.17839)))
("SF_PLANTING" 0 ((2039.96957 3717.94830) (2021.11640 3714.17839)))
("SF_ARCHITECTURE" 0 ((2028.65735 4434.38914) (2036.19910 4419.30577)))
("SF_ARCHITECTURE" 0 ((2028.65735 1613.87726) (2028.65735 1610.10464) (2039.96957 1602.56505)))
("SF_ARCHITECTURE" 0 ((2051.28179 4434.38914) (2046.45532 4423.23156) (2036.19910 4419.30577)))
("SF_PLANTING" 0 ((2081.44796 3631.22172) (2036.19910 3627.45057)))
("SF_PLANTING" 0 ((2055.05305 3438.91403) (2036.19910 3416.28959)))
("SF_ARCHITECTURE" 0 ((2039.96957 4445.70136) (2051.28179 4434.38914)))
("SF_PLANTING" 0 ((2043.74084 3947.96380) (2039.96957 3978.12930)))
("SF_PLANTING" 0 ((2039.96957 3978.12930) (2047.51787 3985.36821) (2077.67749 3978.27771) (2104.07240 3981.90045)))
("SF_ARCHITECTURE" 0 ((2088.98971 1662.89593) (2054.90475 1613.87726) (2039.96957 1602.56505)))
("SF_PLANTING" 0 ((2043.74084 3947.96380) (2126.69683 3948.11844) (2141.77952 3959.27602)))
("SF_PLANTING" 0 ((2047.51131 1131.22172) (2047.36301 1153.83925) (2043.74084 1161.38857)))
("SF_PLANTING" 0 ((2119.15509 1153.84615) (2111.46584 1168.77489) (2100.30192 1172.70079) (2092.76018 1172.70079)
(2062.59400 1168.78111) (2043.74084 1161.38857)))
("SF_PLANTING" 0 ((2066.36527 1097.28507) (2054.00317 1127.29661) (2047.51131 1131.22172)))
("SF_ARCHITECTURE" 0 ((2051.28179 4434.38914) (2088.98971 4487.17907)))
("SF_PLANTING" 0 ((2051.28179 3672.69943) (2081.44796 3665.15837)))
("SF_PLANTING" 0 ((2051.28179 3672.69943) (2058.97839 3694.12002) (2077.67059 3696.52172) (2085.21844 3702.86618)))
("SF_PLANTING" 0 ((2119.15509 3559.57794) (2092.76018 3554.60882) (2077.67749 3541.92817) (2051.28179 3533.18224)))
("SF_PLANTING" 0 ((2066.36527 1097.28507) (2051.28179 1089.74265)))
("SF_PLANTING" 0 ((2100.30192 3495.47511) (2088.84140 3476.76968) (2070.13575 3469.09333) (2051.58495 3476.76968)
(2055.05305 3495.47511)))
("SF_PLANTING" 0 ((2062.59400 3363.49898) (2077.67749 3374.81120)))
("SF_PLANTING" 0 ((2066.36527 1097.28507) (2119.15509 1097.13733) (2134.23857 1093.51527)))
("SF_PLANTING" 0 ((2111.61414 3371.04072) (2077.67749 3374.81120)))
("SF_PLANTING" 0 ((2092.76018 3408.74785) (2078.73348 3389.89468) (2077.67749 3374.81120)))
("SF_PLANTING" 0 ((2081.44796 3631.22172) (2081.44796 3665.15837)))
("SF_PLANTING" 0 ((2081.44796 3665.15837) (2085.21844 3672.69943)))
("SF_PLANTING" 0 ((2081.44796 3631.22172) (2096.53066 3623.83462) (2111.61414 3623.68066)))
("SF_PLANTING" 0 ((2085.21844 3733.03167) (2078.88179 3721.71946) (2085.21844 3702.86618)))
("SF_PLANTING" 0 ((2130.46731 3717.94830) (2107.84287 3703.92229) (2085.21844 3702.86618)))
("SF_PLANTING" 0 ((2100.30192 3495.47511) (2085.21844 3506.78733)))
("SF_PLANTING" 0 ((2092.76018 3408.74785) (2092.76018 3420.06007)))
("SF_PLANTING" 0 ((2092.76018 3408.74785) (2122.92636 3404.97738)))
("SF_PLANTING" 0 ((2111.61414 3793.36391) (2105.26357 3797.28880) (2097.58088 3819.75826) (2096.53066 3853.69491)))
("SF_PLANTING" 0 ((2096.53066 3853.69491) (2111.61414 3860.18054) (2126.69683 3861.23722)))
("SF_PLANTING" 0 ((2111.61414 3231.52364) (2103.71063 3209.26787) (2096.53066 3208.89921)))
("SF_PLANTING" 0 ((2100.30192 3495.47511) (2119.15509 3495.47511)))
("SF_PLANTING" 0 ((2119.15509 1153.84615) (2107.84321 1143.73880) (2100.30192 1142.53394)))
("SF_PLANTING" 0 ((2141.77952 3959.27602) (2122.92636 3976.92545) (2104.07240 3981.90045)))
("SF_PLANTING" 0 ((2104.07240 931.37161) (2100.45633 889.89536) (2111.61414 874.81052)))
("SF_PLANTING" 0 ((2104.07240 931.37161) (2111.61414 935.14423)))
("SF_PLANTING" 0 ((2107.84287 1025.64197) (2130.09921 1006.57262) (2130.46731 991.70532)))
("SF_PLANTING" 0 ((2107.84287 1025.64197) (2112.81165 1040.72398) (2134.23857 1067.11821)))
("SF_PLANTING" 0 ((2111.61414 3770.73948) (2111.61414 3793.36391)))
("SF_PLANTING" 0 ((2111.61414 3793.36391) (2140.57523 3812.37183) (2145.54423 3838.61278) (2141.77952 3861.23722)))
("SF_PLANTING" 0 ((2111.61414 3770.73948) (2130.46731 3770.73948)))
("SF_PLANTING" 0 ((2126.69683 3612.36776) (2111.61414 3623.68066)))
("SF_PLANTING" 0 ((2122.92636 3661.38722) (2111.61414 3623.68066)))
("SF_PLANTING" 0 ((2111.61414 3371.04072) (2122.91980 3360.93269) (2130.46731 3359.72851)))
("SF_PLANTING" 0 ((2111.61414 3371.04072) (2122.92636 3404.97738)))
("SF_PLANTING" 0 ((2119.15509 969.08088) (2111.76199 953.99604) (2111.61414 935.14423)))
("SF_PLANTING" 0 ((2168.17523 935.14423) (2153.09174 938.90713) (2111.61414 935.14423)))
("SF_PLANTING" 0 ((2111.61414 874.81052) (2156.86301 871.04072)))
("SF_PLANTING" 0 ((2134.23857 818.24943) (2100.30848 818.40475) (2093.96448 822.17534) (2093.81618 844.64649)
(2111.61414 874.81052)))
("SF_PLANTING" 0 ((2122.92636 3661.38722) (2119.15509 3672.69943)))
("SF_PLANTING" 0 ((2119.15509 3559.57794) (2126.69683 3536.95351)))
("SF_PLANTING" 0 ((2119.15509 3559.57794) (2126.69683 3612.36776)))
("SF_PLANTING" 0 ((2126.69683 3480.39242) (2126.69683 3487.93337) (2119.15509 3495.47511)))
("SF_PLANTING" 0 ((2126.69683 3536.95351) (2119.15509 3495.47511)))
("SF_PLANTING" 0 ((2122.92636 3156.10860) (2119.15509 3144.79638)))
("SF_PLANTING" 0 ((2119.15509 1153.84615) (2164.40396 1150.07636)))
("SF_PLANTING" 0 ((2141.77952 3665.15837) (2122.92636 3661.38722)))
("SF_PLANTING" 0 ((2130.46731 3412.51912) (2122.92636 3404.97738)))
("SF_PLANTING" 0 ((2124.81120 3301.28179) (2123.07421 3280.54299) (2127.74627 3265.46029) (2149.15984 3231.52364)
(2145.55079 3216.44016)))
("SF_PLANTING" 0 ((2124.81120 3301.28179) (2130.46731 3359.72851)))
("SF_PLANTING" 0 ((2168.17523 3303.16742) (2124.81120 3301.28179)))
("SF_PLANTING" 0 ((2126.69683 3906.48609) (2126.69683 3861.23722)))
("SF_PLANTING" 0 ((2149.32127 3947.96380) (2136.95305 3914.03337) (2126.69683 3906.48609)))
("SF_PLANTING" 0 ((2141.77952 3861.23722) (2126.69683 3861.23722)))
("SF_PLANTING" 0 ((2153.09174 3627.45057) (2126.69683 3612.36776)))
("SF_PLANTING" 0 ((2126.69683 3536.95351) (2153.09174 3540.72398)))
("SF_PLANTING" 0 ((2126.69683 3480.39242) (2160.63348 3480.39242)))
("SF_PLANTING" 0 ((2130.46731 3412.51912) (2123.08077 3442.68450) (2126.69683 3480.39242)))
("SF_PLANTING" 0 ((2164.40396 3996.98382) (2136.95305 4095.02262) (2119.00724 4128.95928) (2096.53066 4150.53394)
(2062.59400 4169.38778) (2017.34514 4185.36572) (2002.26900 4180.69310) (1995.02387 4170.43699) (2013.72952 4098.79378)
(2028.65735 4083.85848) (2130.46731 4008.29604)))
("SF_PLANTING" 0 ((2145.55079 3733.03167) (2130.46731 3770.73948)))
("SF_PLANTING" 0 ((2183.25792 3778.28054) (2130.46731 3770.73948)))
("SF_PLANTING" 0 ((2130.46731 3717.94830) (2145.55079 3695.32387)))
("SF_PLANTING" 0 ((2130.46731 3717.94830) (2145.55079 3733.03167)))
("SF_PLANTING" 0 ((2130.46731 3412.51912) (2156.86301 3416.28959)))
("SF_PLANTING" 0 ((2168.17523 3389.89468) (2149.17296 3368.32658) (2130.46731 3359.72851)))
("SF_PLANTING" 0 ((2138.00905 641.02658) (2130.46731 637.25396)))
("SF_PLANTING" 0 ((2134.23857 1093.51527) (2134.23857 1067.11821)))
("SF_PLANTING" 0 ((2171.94570 1138.76414) (2156.71471 1116.13971) (2134.23857 1093.51527)))
("SF_PLANTING" 0 ((2134.23857 1067.11821) (2213.42410 1070.89084)))
("SF_PLANTING" 0 ((2171.94570 833.33428) (2160.78179 803.16742) (2160.48518 776.77319) (2155.66527 761.83676)
(2134.23857 742.83654)))
("SF_PLANTING" 0 ((2138.00905 663.65102) (2138.00905 641.02658)))
("SF_PLANTING" 0 ((2138.00905 641.02658) (2187.02839 625.94174)))
("SF_PLANTING" 0 ((2141.77952 3959.27602) (2149.32127 3959.27602)))
("SF_PLANTING" 0 ((2141.77952 3861.23722) (2175.71618 3891.40271)))
("SF_PLANTING" 0 ((2141.77952 3665.15837) (2153.09174 3653.84615)))
("SF_PLANTING" 0 ((2141.77952 3665.15837) (2145.40249 3672.70633) (2145.55079 3695.32387)))
("SF_PLANTING" 0 ((2175.71618 3717.94830) (2145.55079 3733.03167)))
("SF_PLANTING" 0 ((2145.55079 3695.32387) (2175.71618 3702.86618)))
("SF_PLANTING" 0 ((2149.32127 3947.96380) (2149.32127 3959.27602)))
("SF_PLANTING" 0 ((2164.40396 3996.98382) (2163.19966 3974.35939) (2149.32127 3959.27602)))
("SF_PLANTING" 0 ((2149.32127 3947.96380) (2187.02839 3951.73495) (2205.88235 3948.11188) (2266.21391 3947.96380)))
("SF_PLANTING" 0 ((2183.25792 580.69287) (2168.17523 579.48948) (2149.32127 561.84106)))
("SF_PLANTING" 0 ((2160.63348 4144.04265) (2160.47862 4162.88971) (2153.09174 4170.43699)))
("SF_PLANTING" 0 ((2160.63348 4144.04265) (2142.99038 4151.73835) (2146.60023 4166.51210) (2153.09174 4170.43699)))
("SF_PLANTING" 0 ((2156.86301 4189.29152) (2153.09174 4170.43699)))
("SF_PLANTING" 0 ((2153.09174 3653.84615) (2153.09174 3627.45057)))
("SF_PLANTING" 0 ((2153.09174 3653.84615) (2175.71968 3653.99740) (2188.91403 3659.50226)))
("SF_PLANTING" 0 ((2179.48744 3623.68066) (2153.09174 3627.45057)))
("SF_PLANTING" 0 ((2168.17523 3389.89468) (2163.21301 3412.36448) (2156.86301 3416.28959)))
("SF_PLANTING" 0 ((2156.86301 3416.28959) (2149.46957 3450.22624) (2160.63348 3480.39242)))
("SF_PLANTING" 0 ((2156.86301 976.62048) (2168.16867 975.09808) (2175.71618 980.39310)))
("SF_PLANTING" 0 ((2171.94570 833.33428) (2166.97749 848.41629) (2158.06731 859.72851) (2156.86301 871.04072)))
("SF_PLANTING" 0 ((2156.86301 871.04072) (2171.94570 882.35294)))
("SF_PLANTING" 0 ((2160.63348 4144.04265) (2171.94570 4130.16380) (2205.88235 4125.18812)))
("SF_PLANTING" 0 ((2164.40396 3491.70464) (2160.63348 3480.39242)))
("SF_PLANTING" 0 ((2160.63348 1327.29921) (2179.48744 1313.42206) (2209.65283 1308.44740)))
("SF_PLANTING" 0 ((2164.40396 3996.98382) (2179.48744 4001.81041) (2190.79966 4010.86210) (2217.19457 4015.83710)))
("SF_PLANTING" 0 ((2168.17523 3303.16742) (2164.40396 3325.79186)))
("SF_PLANTING" 0 ((2164.40396 1150.07636) (2171.94570 1138.76414)))
("SF_PLANTING" 0 ((2164.40396 1150.07636) (2152.04231 1184.01301) (2133.18213 1217.94966) (2056.24400 1331.07183)
(2051.43665 1346.15385) (2055.20747 1356.26120) (2073.90622 1356.26810) (2107.84287 1333.79219) (2140.73009 1297.13518)
(2152.03575 1278.28054) (2161.68292 1233.03167) (2175.71618 1195.32523)))
("SF_PLANTING" 0 ((2168.17523 3389.89468) (2182.05339 3378.58247) (2179.48744 3359.72851)))
("SF_PLANTING" 0 ((2349.17070 3299.39695) (2179.48744 3299.40317) (2168.17523 3303.16742)))
("SF_PLANTING" 0 ((2168.17523 935.14423) (2168.32308 893.66516) (2171.94570 882.35294)))
("SF_PLANTING" 0 ((2198.34061 938.91403) (2168.17523 935.14423)))
("SF_PLANTING" 0 ((2220.96505 1150.07636) (2171.94570 1138.76414)))
("SF_PLANTING" 0 ((2209.65283 878.58314) (2171.94570 882.35294)))
("SF_PLANTING" 0 ((2171.94570 833.33428) (2213.42410 833.33428)))
("SF_PLANTING" 0 ((2190.79966 682.50283) (2171.94570 686.27545)))
("SF_PLANTING" 0 ((2175.71618 3717.94830) (2175.71618 3702.86618)))
("SF_PLANTING" 0 ((2200.22624 3731.14672) (2175.71618 3717.94830)))
("SF_PLANTING" 0 ((2175.71618 3702.86618) (2189.59536 3687.78281) (2188.91403 3659.50226)))
("SF_PLANTING" 0 ((2179.48744 3623.68066) (2195.62613 3593.51459) (2208.44853 3578.43111) (2213.42410 3542.60962)))
("SF_PLANTING" 0 ((2179.48744 3623.68066) (2188.91403 3659.50226)))
("SF_PLANTING" 0 ((2200.22624 3731.14672) (2184.45566 3766.96833) (2183.25792 3778.28054)))
("SF_PLANTING" 0 ((2183.25792 3778.28054) (2198.34061 3785.82161)))
("SF_PLANTING" 0 ((2183.25792 580.69287) (2202.11188 576.92308)))
("SF_PLANTING" 0 ((2183.25792 580.69287) (2187.02839 625.94174)))
("SF_PLANTING" 0 ((2209.65283 1257.54242) (2190.95407 1268.01776) (2187.02839 1274.51075)))
("SF_PLANTING" 0 ((2187.02839 1014.32975) (2207.76799 1016.21324)))
("SF_PLANTING" 0 ((2194.57014 629.71437) (2187.02839 625.94174)))
("SF_PLANTING" 0 ((2232.27726 3634.99287) (2198.27353 3660.11572) (2188.91403 3659.50226)))
("SF_PLANTING" 0 ((2190.79966 720.21210) (2194.57014 693.81505)))
("SF_PLANTING" 0 ((2190.79966 682.50283) (2194.57014 629.71437)))
("SF_PLANTING" 0 ((2190.79966 682.50283) (2194.57014 693.81505)))
("SF_PLANTING" 0 ((2224.73631 475.11312) (2202.25973 467.41742) (2190.79966 444.94627)))
("SF_PLANTING" 0 ((2213.42410 3542.60962) (2194.57014 3536.95351)))
("SF_PLANTING" 0 ((2202.11188 757.91855) (2198.34061 757.91855) (2194.57014 746.60633)))
("SF_PLANTING" 0 ((2245.47511 695.70136) (2194.57014 693.81505)))
("SF_PLANTING" 0 ((2232.27726 629.71437) (2194.57014 629.71437)))
("SF_PLANTING" 0 ((2232.27726 3751.88495) (2198.34061 3785.82161)))
("SF_PLANTING" 0 ((2220.96505 3834.84163) (2210.70305 3823.52941) (2198.34061 3785.82161)))
("SF_PLANTING" 0 ((2228.50679 923.83201) (2209.65317 928.79977) (2198.34061 938.91403)))
("SF_PLANTING" 0 ((2198.34061 938.91403) (2209.65283 961.53846)))
("SF_PLANTING" 0 ((2198.34061 550.52885) (2202.11188 576.92308)))
("SF_PLANTING" 0 ((2200.22624 3731.14672) (2236.04853 3710.40724)))
("SF_PLANTING" 0 ((2200.22624 3731.14672) (2213.42059 3739.37206) (2232.27726 3740.57274)))
("SF_PLANTING" 0 ((2232.27726 3849.92500) (2223.67986 3883.86165) (2202.11188 3917.79830)))
("SF_PLANTING" 0 ((2236.04853 750.37613) (2202.11188 757.91855)))
("SF_PLANTING" 0 ((2202.11188 757.91855) (2198.48891 784.31278) (2213.42410 833.33428)))
("SF_PLANTING" 0 ((2228.50679 584.46550) (2202.11188 576.92308)))
("SF_PLANTING" 0 ((2213.42410 4095.02262) (2205.88235 4125.18812)))
("SF_PLANTING" 0 ((2207.76799 1016.21324) (2243.58948 1014.32975)))
("SF_PLANTING" 0 ((2207.76799 1016.21324) (2205.88891 991.70532) (2209.65283 961.53846)))
("SF_PLANTING" 0 ((2207.76799 1016.21324) (2213.42410 1070.89084)))
("SF_PLANTING" 0 ((2217.19457 3480.39242) (2209.65283 3476.62115)))
("SF_PLANTING" 0 ((2209.65283 1257.54242) (2213.12783 1266.90068) (2209.65283 1308.44740)))
("SF_PLANTING" 0 ((2209.65283 1257.54242) (2247.36075 1255.65611)))
("SF_PLANTING" 0 ((2209.65283 1257.54242) (2209.80113 1191.55260) (2219.90905 1168.92817) (2220.96505 1150.07636)))
("SF_PLANTING" 0 ((2209.65283 961.53846) (2239.81244 961.39072) (2247.36075 957.76867)))
("SF_PLANTING" 0 ((2224.73631 878.58314) (2209.65283 878.58314)))
("SF_PLANTING" 0 ((2209.65283 878.58314) (2213.42410 833.33428)))
("SF_PLANTING" 0 ((2213.42410 4095.02262) (2254.90192 4091.25147)))
("SF_PLANTING" 0 ((2217.19457 4023.37817) (2213.57195 4030.92670) (2213.42410 4095.02262)))
("SF_PLANTING" 0 ((2213.42410 3542.60962) (2220.81719 3518.09955) (2217.19457 3480.39242)))
("SF_PLANTING" 0 ((2251.13122 3548.26572) (2228.50679 3548.11719) (2213.42410 3542.60962)))
("SF_PLANTING" 0 ((2232.27726 3435.14355) (2213.42410 3431.37229)))
("SF_PLANTING" 0 ((2213.42410 1070.89084) (2228.50679 1081.14593) (2239.81900 1082.20305)))
("SF_PLANTING" 0 ((2239.81900 833.33428) (2213.42410 833.33428)))
("SF_PLANTING" 0 ((2217.19457 4023.37817) (2217.19457 4015.83710)))
("SF_PLANTING" 0 ((2217.19457 4023.37817) (2236.04853 4024.43484) (2249.93348 4034.69729) (2254.90192 4049.77376)
(2254.90192 4091.25147)))
("SF_PLANTING" 0 ((2224.73631 3989.44152) (2217.19457 4015.83710)))
("SF_PLANTING" 0 ((2232.27726 3476.62115) (2220.96505 3476.62115) (2217.19457 3480.39242)))
("SF_PLANTING" 0 ((2224.73631 380.84559) (2217.19457 377.07296)))
("SF_PLANTING" 0 ((2220.96505 3834.84163) (2224.73631 3842.38269) (2230.39242 3842.38269)))
("SF_PLANTING" 0 ((2220.96505 3834.84163) (2230.39242 3842.38269)))
("SF_PLANTING" 0 ((2220.96505 1150.07636) (2254.90170 1138.91120) (2273.75566 1140.64762)))
("SF_PLANTING" 0 ((2228.50679 505.27907) (2220.96505 505.27907)))
("SF_PLANTING" 0 ((2243.58948 569.38066) (2222.02149 527.90441) (2220.96505 505.27907)))
("SF_PLANTING" 0 ((2224.73631 328.05430) (2220.96505 320.51188)))
("SF_PLANTING" 0 ((2224.73631 878.58314) (2238.61471 871.03382) (2243.57636 848.41629) (2239.81900 833.33428)))
("SF_PLANTING" 0 ((2228.50679 923.83201) (2224.73631 878.58314)))
("SF_PLANTING" 0 ((2224.73631 475.11312) (2232.27726 452.48869)))
("SF_PLANTING" 0 ((2224.73631 475.11312) (2228.50679 505.27907)))
("SF_PLANTING" 0 ((2224.73631 380.84559) (2224.73631 411.00962)))
("SF_PLANTING" 0 ((2224.73631 380.84559) (2236.04853 380.84559)))
("SF_PLANTING" 0 ((2228.50679 923.83201) (2247.36075 938.91403)))
("SF_PLANTING" 0 ((2228.50679 584.46550) (2243.58948 569.38066)))
("SF_PLANTING" 0 ((2239.81900 599.54751) (2233.32715 595.62240) (2228.50679 584.46550)))
("SF_PLANTING" 0 ((2269.98518 505.27907) (2228.50679 505.27907)))
("SF_PLANTING" 0 ((2254.90170 3808.44604) (2246.31052 3827.30057) (2230.39242 3842.38269)))
("SF_PLANTING" 0 ((2232.27726 3849.92500) (2230.39242 3842.38269)))
("SF_PLANTING" 0 ((2232.27726 3849.92500) (2254.90170 3861.23722)))
("SF_PLANTING" 0 ((2232.27726 3740.57274) (2232.27726 3751.88495)))
("SF_PLANTING" 0 ((2232.27726 3751.88495) (2251.13122 3755.64299) (2266.21391 3751.88495)))
("SF_PLANTING" 0 ((2232.27726 3740.57274) (2235.90023 3733.02545) (2236.04853 3710.40724)))
("SF_PLANTING" 0 ((2243.58948 3582.20238) (2232.27726 3634.99287)))
("SF_PLANTING" 0 ((2258.67296 3642.53394) (2232.27726 3634.99287)))
("SF_PLANTING" 0 ((2232.27726 3435.14355) (2232.27726 3476.62115)))
("SF_PLANTING" 0 ((2232.27726 3476.62115) (2251.13122 3480.39242)))
("SF_PLANTING" 0 ((2232.27726 3435.14355) (2232.27726 3416.28959)))
("SF_PLANTING" 0 ((2232.27726 629.71437) (2239.81900 629.71437)))
("SF_PLANTING" 0 ((2232.27726 629.71437) (2233.48156 671.19061) (2247.36075 682.50283)))
("SF_PLANTING" 0 ((2254.90170 3680.24174) (2241.01674 3691.55396) (2236.04853 3710.40724)))
("SF_PLANTING" 0 ((2245.47511 695.70136) (2236.19638 712.66968) (2236.04853 750.37613)))
("SF_PLANTING" 0 ((2236.04853 750.37613) (2258.67296 761.68835)))
("SF_PLANTING" 0 ((2273.75566 1044.49378) (2239.81900 1082.20305)))
("SF_PLANTING" 0 ((2239.81900 1082.20305) (2262.44344 1093.51527)))
("SF_PLANTING" 0 ((2243.58948 829.56165) (2239.81900 833.33428)))
("SF_PLANTING" 0 ((2243.58948 829.56165) (2239.81900 829.56165) (2239.81900 833.33428)))
("SF_PLANTING" 0 ((2239.81900 599.54751) (2239.81900 629.71437)))
("SF_PLANTING" 0 ((2266.21391 644.79638) (2258.66606 634.68903) (2239.81900 629.71437)))
("SF_PLANTING" 0 ((2239.81900 599.54751) (2253.69740 591.85803) (2258.67296 569.38066)))
("SF_PLANTING" 0 ((2251.13122 965.30826) (2243.58948 1014.32975)))
("SF_PLANTING" 0 ((2273.75566 1044.49378) (2243.58948 1014.32975)))
("SF_PLANTING" 0 ((2285.06787 829.56165) (2243.58948 829.56165)))
("SF_PLANTING" 0 ((2243.58948 806.93722) (2243.58948 829.56165)))
("SF_PLANTING" 0 ((2258.67296 569.38066) (2243.58948 569.38066)))
("SF_PLANTING" 0 ((2245.47511 695.70136) (2247.36075 682.50283)))
("SF_PLANTING" 0 ((2245.47511 695.70136) (2269.98518 705.12726)))
("SF_PLANTING" 0 ((2247.36075 1255.65611) (2273.75566 1225.48925)))
("SF_PLANTING" 0 ((2247.36075 1255.65611) (2254.75385 1285.82296) (2255.05000 1323.52941) (2262.44344 1349.92364)))
("SF_PLANTING" 0 ((2247.36075 938.91403) (2247.36075 957.76867)))
("SF_PLANTING" 0 ((2251.13122 965.30826) (2247.36075 957.76867)))
("SF_PLANTING" 0 ((2247.36075 938.91403) (2269.98484 917.49446) (2277.52613 916.28959)))
("SF_PLANTING" 0 ((2266.21391 644.79638) (2261.23914 667.42081) (2247.36075 682.50283)))
("SF_PLANTING" 0 ((2254.90170 3861.23722) (2251.13122 3872.54943)))
("SF_PLANTING" 0 ((2251.13122 3548.26572) (2251.13122 3563.34842)))
("SF_PLANTING" 0 ((2251.13122 3548.26572) (2262.28857 3525.64129) (2258.67296 3514.32907)))
("SF_PLANTING" 0 ((2300.15057 957.76867) (2251.13122 965.30826)))
("SF_PLANTING" 0 ((2254.90170 3861.23722) (2262.30204 3857.31143) (2287.63405 3823.52941) (2300.00271 3789.59276)
(2301.35486 3759.43348) (2307.69887 3752.94163) (2322.77500 3748.11505)))
("SF_PLANTING" 0 ((2258.67296 3642.53394) (2254.90170 3680.24174)))
("SF_PLANTING" 0 ((2254.90170 3680.24174) (2296.38009 3684.01165)))
("SF_PLANTING" 0 ((2254.90170 429.86425) (2258.67296 414.78224)))
("SF_PLANTING" 0 ((2254.90192 4174.20814) (2277.52613 4174.05351) (2285.06131 4170.28303) (2300.15057 4144.04265)))
("SF_PLANTING" 0 ((2254.90192 4174.20814) (2254.90192 4162.89593) (2254.90192 4091.25147)))
("SF_PLANTING" 0 ((2281.29740 3642.53394) (2258.67296 3642.53394)))
("SF_PLANTING" 0 ((2258.67296 780.54299) (2258.67296 761.68835)))
("SF_PLANTING" 0 ((2258.67296 761.68835) (2300.15057 757.91855)))
("SF_PLANTING" 0 ((2258.67296 569.38066) (2273.75566 565.61086)))
("SF_PLANTING" 0 ((2285.06787 1353.69627) (2262.44344 1349.92364)))
("SF_PLANTING" 0 ((2281.29740 1044.49378) (2284.00532 1059.57862) (2262.44344 1093.51527)))
("SF_PLANTING" 0 ((2273.75566 1119.90950) (2267.27036 1112.36222) (2262.44344 1093.51527)))
("SF_PLANTING" 0 ((2285.06787 3898.94378) (2274.81165 3914.02715) (2266.21391 3947.96380)))
("SF_PLANTING" 0 ((2275.64129 3957.39106) (2269.98518 3955.50486) (2266.21391 3947.96380)))
("SF_PLANTING" 0 ((2277.52613 641.02658) (2266.21391 644.79638)))
("SF_PLANTING" 0 ((2269.98518 505.27907) (2266.21391 535.44400)))
("SF_PLANTING" 0 ((2269.98518 505.27907) (2364.25339 505.27907)))
("SF_PLANTING" 0 ((2273.75566 4000.75373) (2292.60962 3989.44152)))
("SF_PLANTING" 0 ((2275.64129 3957.39106) (2262.60486 3974.35939) (2267.40509 3993.20645) (2273.75566 4000.75373)))
("SF_PLANTING" 0 ((2273.75566 4000.75373) (2287.78235 4027.14932) (2292.46131 4046.00260) (2296.38009 4102.56369)))
("SF_PLANTING" 0 ((2273.75566 1176.47059) (2273.75566 1225.48925)))
("SF_PLANTING" 0 ((2296.38009 1274.51075) (2291.55939 1244.34389) (2284.91957 1233.03857) (2273.75566 1225.48925)))
("SF_PLANTING" 0 ((2273.75566 1140.64762) (2273.75566 1176.47059)))
("SF_PLANTING" 0 ((2273.75566 1176.47059) (2303.76697 1184.16629) (2312.51957 1210.40102) (2330.31674 1224.29208)
(2358.59729 1229.26188)))
("SF_PLANTING" 0 ((2273.75566 1140.64762) (2273.75566 1119.90950)))
("SF_PLANTING" 0 ((2349.17070 1142.53394) (2334.08722 1139.05962) (2319.00452 1142.52771) (2273.75566 1140.64762)))
("SF_PLANTING" 0 ((2366.13903 1061.46210) (2311.46278 1103.62262) (2288.83835 1109.79525) (2273.75566 1119.90950)))
("SF_PLANTING" 0 ((2281.29740 1044.49378) (2273.75566 1044.49378)))
("SF_PLANTING" 0 ((2275.64129 3957.39106) (2307.69231 3956.56154) (2356.71165 3978.12930)))
("SF_PLANTING" 0 ((2275.64129 3957.39106) (2291.40532 3978.12930) (2292.60962 3989.44152)))
("SF_PLANTING" 0 ((2292.60962 3367.27025) (2277.52613 3363.49898)))
("SF_PLANTING" 0 ((2277.52613 916.28959) (2278.58258 897.43495) (2296.38009 855.95871)))
("SF_PLANTING" 0 ((2277.52613 916.28959) (2296.38009 920.05939)))
("SF_PLANTING" 0 ((2320.89016 967.19457) (2305.12613 984.16290) (2299.09457 1021.86934) (2281.29740 1044.49378)))
("SF_PLANTING" 0 ((2405.73179 3898.94378) (2394.41923 3888.82941) (2371.79514 3883.86165) (2352.94118 3884.91120)
(2326.54627 3895.02545) (2285.06787 3898.94378)))
("SF_PLANTING" 0 ((2285.06787 3898.94378) (2296.53495 3868.92636) (2319.00452 3853.54706) (2356.71165 3816.14231)
(2375.56561 3807.38993) (2385.67353 3797.13382) (2383.10735 3751.88495)))
("SF_PLANTING" 0 ((2296.38009 1274.51075) (2288.99321 1285.82296) (2288.98665 1304.67477) (2298.95305 1331.07183)
(2295.17590 1346.14695) (2285.06787 1353.69627)))
("SF_PLANTING" 0 ((2285.06787 1353.69627) (2288.83835 1365.00848)))
("SF_PLANTING" 0 ((2285.06787 829.56165) (2288.99321 818.24943) (2307.69231 803.16742)))
("SF_PLANTING" 0 ((2285.06787 829.56165) (2296.38009 855.95871)))
("SF_PLANTING" 0 ((2326.54627 4034.69038) (2292.60962 3989.44152)))
("SF_PLANTING" 0 ((2296.38009 1274.51075) (2303.92839 1275.71414) (2322.77500 1293.36256)))
("SF_PLANTING" 0 ((2326.54627 852.18609) (2330.16844 867.27093) (2321.57070 897.43495) (2296.38009 920.05939)))
("SF_PLANTING" 0 ((2300.15057 957.76867) (2296.38009 920.05939)))
("SF_PLANTING" 0 ((2296.38009 855.95871) (2326.54627 852.18609)))
("SF_PLANTING" 0 ((2320.89016 967.19457) (2300.15057 957.76867)))
("SF_PLANTING" 0 ((2300.15057 757.91855) (2315.23405 747.66267) (2337.85848 746.60633)))
("SF_PLANTING" 0 ((2300.15057 757.91855) (2307.69231 803.16742)))
("SF_PLANTING" 0 ((2307.69231 4121.41821) (2360.48292 4125.18812)))
("SF_PLANTING" 0 ((2330.31674 840.87387) (2317.94853 810.71471) (2307.69231 803.16742)))
("SF_PLANTING" 0 ((2319.00452 4072.39819) (2326.69412 4082.51278) (2360.48292 4087.48156)))
("SF_PLANTING" 0 ((2322.77500 1293.36256) (2319.00452 1304.67477)))
("SF_PLANTING" 0 ((2320.89016 967.19457) (2334.08722 957.76867)))
("SF_PLANTING" 0 ((2320.89016 967.19457) (2336.65385 984.16290) (2341.62896 1003.01753)))
("SF_PLANTING" 0 ((2334.08722 3344.64581) (2330.32986 3367.27025) (2333.93937 3382.35294) (2334.08066 3427.60181)
(2330.31674 3450.22624) (2330.32330 3650.07500) (2334.08066 3699.09502) (2322.77500 3748.11505)))
("SF_PLANTING" 0 ((2383.10735 3751.88495) (2334.08756 3751.73710) (2322.77500 3748.11505)))
("SF_PLANTING" 0 ((2360.48292 1293.36256) (2322.77500 1293.36256)))
("SF_PLANTING" 0 ((2330.31674 840.87387) (2326.54627 852.18609)))
("SF_PLANTING" 0 ((2330.31674 840.87387) (2349.17070 840.87387)))
("SF_PLANTING" 0 ((2330.31674 780.54299) (2341.62896 761.68835)))
("SF_PLANTING" 0 ((2386.87783 3936.65158) (2364.25339 3932.88043) (2334.08722 3936.65158)))
("SF_PLANTING" 0 ((2379.33609 938.91403) (2345.39977 956.71154) (2334.08722 957.76867)))
("SF_PLANTING" 0 ((2375.56561 901.20758) (2356.71821 894.87624) (2350.22014 897.59729) (2338.91448 916.28959)
(2334.08722 957.76867)))
("SF_PLANTING" 0 ((2352.94118 727.75170) (2346.44932 731.67760) (2337.85848 746.60633)))
("SF_PLANTING" 0 ((2341.62896 761.68835) (2337.85848 757.91855) (2337.85848 746.60633)))
("SF_PLANTING" 0 ((2345.39943 690.04525) (2337.85848 690.04525)))
("SF_PLANTING" 0 ((2341.62896 4038.46154) (2352.94118 4042.23269)))
("SF_PLANTING" 0 ((2341.62896 1003.01753) (2360.48292 998.04774) (2374.50962 984.16290) (2385.82839 957.76867)
(2386.87783 938.91403)))
("SF_PLANTING" 0 ((2341.62896 1003.01753) (2346.45622 1033.18156) (2366.13903 1061.46210)))
("SF_PLANTING" 0 ((2371.79514 765.46097) (2364.24683 761.83676) (2341.62896 761.68835)))
("SF_PLANTING" 0 ((2356.71165 629.71437) (2351.41776 633.63880) (2352.79287 671.19061) (2345.39943 690.04525)))
("SF_PLANTING" 0 ((2345.39943 690.04525) (2352.94118 727.75170)))
("SF_PLANTING" 0 ((2349.17070 3299.39695) (2356.71855 3289.28258) (2371.79514 3284.46120) (2386.72952 3285.51765)
(2392.31335 3295.62568) (2389.45735 3306.78326) (2383.10735 3310.70916)))
("SF_PLANTING" 0 ((2349.17070 3299.39695) (2360.48292 3309.50498) (2383.10735 3310.70916)))
("SF_PLANTING" 0 ((2349.17070 1142.53394) (2364.25339 1135.13993) (2420.81448 1131.22172)))
("SF_PLANTING" 0 ((2349.17070 1142.53394) (2360.33462 1214.17704) (2358.59729 1229.26188)))
("SF_PLANTING" 0 ((2375.56561 806.93722) (2349.17070 840.87387)))
("SF_PLANTING" 0 ((2349.17070 840.87387) (2360.48292 850.98269) (2386.87783 855.95871)))
("SF_PLANTING" 0 ((2364.25339 4008.29604) (2357.90939 4015.84333) (2352.94118 4042.23269)))
("SF_PLANTING" 0 ((2360.48292 4068.62704) (2352.94118 4042.23269)))
("SF_PLANTING" 0 ((2375.56561 735.29412) (2352.94118 727.75170)))
("SF_ARCHITECTURE" 0 ((2356.71165 5071.64446) (2360.48292 5090.49774) (2356.71165 5135.74661)))
("SF_ARCHITECTURE" 0 ((2356.71165 5135.74661) (2360.33462 5143.29457) (2360.63733 5192.30769) (2364.40826 5199.69480)
(2371.79514 5203.46527) (2401.96052 5203.46527) (2417.04400 5192.30769)))
("SF_ARCHITECTURE" 0 ((2356.71165 5071.64446) (2356.71821 4683.25792) (2360.47636 4664.40464) (2356.71821 4630.46799)
(2360.48292 4607.84355) (2356.71821 4566.36459) (2356.71821 4166.66708) (2360.48292 4147.81256)))
("SF_PLANTING" 0 ((2356.71165 3978.12930) (2364.40170 3968.02183) (2383.10735 3966.81708)))
("SF_PLANTING" 0 ((2364.25339 4008.29604) (2356.71165 3978.12930)))
("SF_PLANTING" 0 ((2356.71165 629.71437) (2356.71165 622.17195)))
("SF_PLANTING" 0 ((2356.71165 629.71437) (2386.94186 629.86765) (2394.05068 633.63880) (2387.03269 690.03903)
(2398.19005 701.35747)))
("SF_PLANTING" 0 ((2360.48292 1293.36256) (2356.71821 1274.51075) (2358.59729 1229.26188)))
("SF_PLANTING" 0 ((2358.59729 1229.26188) (2401.96052 1241.77127) (2417.04400 1263.19853)))
("SF_PLANTING" 0 ((2413.27274 4147.81256) (2360.48292 4147.81256)))
("SF_PLANTING" 0 ((2360.48292 4125.18812) (2360.48292 4147.81256)))
("SF_PLANTING" 0 ((2360.48292 4087.48156) (2360.48292 4125.18812)))
("SF_PLANTING" 0 ((2360.48292 4068.62704) (2360.48292 4087.48156)))
("SF_PLANTING" 0 ((2360.48292 4068.62704) (2375.56561 4069.68371) (2390.64830 4077.22477) (2413.27274 4102.56369)))
("SF_PLANTING" 0 ((2375.56561 3853.69491) (2360.48292 3857.46606)))
("SF_ARCHITECTURE" 0 ((2360.48292 2251.13122) (2364.25317 2273.75566) (2360.48292 2311.46278)))
("SF_ARCHITECTURE" 0 ((2417.04400 2349.17070) (2398.19005 2360.33439) (2368.03077 2359.27873) (2360.63733 2349.17070)
(2360.48292 2311.46278)))
("SF_ARCHITECTURE" 0 ((2360.48292 1304.67477) (2356.71165 1323.52941) (2360.48269 1640.27149) (2360.48269 1662.89593)
(2360.48269 2088.98971) (2360.48269 2104.07240) (2360.48269 2183.25792) (2360.48269 2198.34061) (2360.48292
2251.13122)))
("SF_PLANTING" 0 ((2360.48292 1293.36256) (2360.48292 1304.67477)))
("SF_PLANTING" 0 ((2413.27274 1308.44740) (2360.48292 1304.67477)))
("SF_PLANTING" 0 ((2413.27274 4027.14932) (2401.96052 4026.09265) (2364.25339 4008.29604)))
("SF_PLANTING" 0 ((2364.25339 505.27907) (2511.31222 505.27907) (2521.42014 512.97489) (2522.77274 625.94174)
(2526.38835 641.02658) (2526.24706 690.04525) (2522.63100 705.12726) (2522.62443 931.37161)))
("SF_PLANTING" 0 ((2364.25339 505.27907) (2360.63077 569.38066) (2368.02387 588.23529)))
("SF_PLANTING" 0 ((2366.13903 1061.46210) (2390.79661 1025.64197) (2432.12670 984.16290)))
("SF_PLANTING" 0 ((2401.96052 1070.89084) (2386.87783 1069.83993) (2366.13903 1061.46210)))
("SF_PLANTING" 0 ((2379.33609 754.14876) (2371.79514 765.46097)))
("SF_PLANTING" 0 ((2375.56561 806.93722) (2368.32014 776.77319) (2371.79514 765.46097)))
("SF_PLANTING" 0 ((2375.56561 901.20758) (2390.49389 886.11787) (2386.87783 855.95871)))
("SF_PLANTING" 0 ((2379.33609 938.91403) (2375.56561 901.20758)))
("SF_PLANTING" 0 ((2375.56561 806.93722) (2390.64830 806.93722)))
("SF_PLANTING" 0 ((2375.56561 735.29412) (2405.73179 731.52432)))
("SF_PLANTING" 0 ((2379.33609 754.14876) (2375.71391 750.22285) (2375.56561 735.29412)))
("SF_PLANTING" 0 ((2379.33609 938.91403) (2386.87783 938.91403)))
("SF_PLANTING" 0 ((2379.33609 754.14876) (2390.64864 753.09163) (2401.80611 746.45792) (2405.73179 731.52432)))
("SF_PLANTING" 0 ((2386.87783 3936.65158) (2383.10735 3966.81708)))
("SF_PLANTING" 0 ((2409.50226 3978.12930) (2383.10735 3966.81708)))
("SF_PLANTING" 0 ((2383.10735 3751.88495) (2383.10079 3563.34842) (2379.33609 3540.72398) (2383.10079 3514.32907)
(2379.33609 3378.58247) (2383.10735 3310.70916)))
("SF_PLANTING" 0 ((2386.87783 3936.65158) (2405.73179 3932.88043)))
("SF_PLANTING" 0 ((2386.87783 3239.06459) (2390.64830 3220.21143) (2386.88439 3080.69355) (2390.64830 3069.38133)))
("SF_PLANTING" 0 ((2413.27274 931.37161) (2386.87783 938.91403)))
("SF_PLANTING" 0 ((2390.64830 806.93722) (2394.26471 844.64649) (2386.87783 855.95871)))
("SF_PLANTING" 0 ((2409.50226 1199.09502) (2390.64830 1180.24038)))
("SF_PLANTING" 0 ((2390.64830 806.93722) (2398.19005 803.16742)))
("SF_PLANTING" 0 ((2398.19005 701.35747) (2409.50226 697.58767)))
("SF_PLANTING" 0 ((2398.19005 701.35747) (2405.73179 731.52432)))
("SF_PLANTING" 0 ((2401.96052 3842.38269) (2420.81448 3838.45781) (2450.98066 3804.67613)))
("SF_PLANTING" 0 ((2401.96052 1070.89084) (2420.81448 1053.08563) (2450.98066 1040.72398)))
("SF_PLANTING" 0 ((2401.96052 1070.89084) (2404.83654 1089.74265) (2420.81448 1108.59729)))
("SF_PLANTING" 0 ((2405.73179 3898.94378) (2405.73179 3932.88043)))
("SF_PLANTING" 0 ((2424.58495 3951.73495) (2405.73179 3932.88043)))
("SF_PLANTING" 0 ((2405.73179 3898.94378) (2443.43891 3887.77998) (2499.99344 3887.77998) (2507.54174 3891.40271)))
("SF_PLANTING" 0 ((2409.50226 3978.12930) (2419.75848 3966.81708) (2424.58495 3951.73495)))
("SF_PLANTING" 0 ((2424.58495 4008.29604) (2409.50226 3978.12930)))
("SF_PLANTING" 0 ((2413.27274 4147.81256) (2413.27274 4102.56369)))
("SF_PLANTING" 0 ((2417.04400 4166.66708) (2413.27274 4147.81256)))
("SF_PLANTING" 0 ((2477.37557 4096.90758) (2424.58529 4098.94163) (2413.27274 4102.56369)))
("SF_PLANTING" 0 ((2413.27274 4027.14932) (2424.58495 4008.29604)))
("SF_PLANTING" 0 ((2413.27274 4027.14932) (2424.58529 4041.02794) (2439.66154 4041.02794) (2447.05498 4030.91980)
(2447.20939 4008.29604)))
("SF_PLANTING" 0 ((2413.27274 1308.44740) (2417.04400 1263.19853)))
("SF_PLANTING" 0 ((2413.27274 1308.44740) (2413.42104 1327.14593) (2417.04400 1331.07183)))
("SF_PLANTING" 0 ((2413.27274 554.29864) (2450.98066 550.52885)))
("SF_ARCHITECTURE" 0 ((2417.04400 4166.66708) (2417.04400 5192.30769)))
("SF_ARCHITECTURE" 0 ((2417.04400 5192.30769) (2432.12670 5202.41572) (2469.83382 5203.46527) (2484.91731 5192.30769)))
("SF_PLANTING" 0 ((2417.04400 4166.66708) (2484.91731 4166.66708)))
("SF_ARCHITECTURE" 0 ((2417.04400 2315.23405) (2417.04400 2349.17070)))
("SF_ARCHITECTURE" 0 ((2477.37557 2356.71165) (2469.82726 2360.33518) (2435.89717 2360.32828) (2417.04400 2349.17070)))
("SF_ARCHITECTURE" 0 ((2417.04400 2315.23405) (2427.29977 2307.68541) (2432.12670 2288.83835) (2430.92240 2269.98518)
(2417.04400 2254.90170)))
("SF_ARCHITECTURE" 0 ((2417.04400 2315.23405) (2401.96075 2307.68541) (2401.96075 2288.83835) (2401.96075 2273.75566)
(2417.04400 2254.90170)))
("SF_ARCHITECTURE" 0 ((2417.04400 2254.90170) (2417.04400 1331.07183)))
("SF_PLANTING" 0 ((2484.91731 1331.07183) (2417.04400 1331.07183)))
("SF_PLANTING" 0 ((2435.89717 1259.42590) (2417.04400 1263.19853)))
("SF_PLANTING" 0 ((2420.81448 1108.59729) (2420.81448 1131.22172)))
("SF_PLANTING" 0 ((2420.81448 1131.22172) (2451.12817 1182.95588) (2481.14604 1198.94661) (2518.85396 1199.09502)))
("SF_PLANTING" 0 ((2420.81448 1108.59729) (2435.89717 1108.59729)))
("SF_PLANTING" 0 ((2420.81448 844.64649) (2431.97183 840.72059) (2435.74276 833.33428) (2434.69966 818.25701)
(2428.35622 810.70984)))
("SF_PLANTING" 0 ((2424.58495 4008.29604) (2447.20939 4008.29604)))
("SF_PLANTING" 0 ((2424.58495 3951.73495) (2458.52161 3951.73495)))
("SF_PLANTING" 0 ((2677.22500 3733.03167) (2435.89751 3733.02545) (2424.58495 3729.26052)))
("SF_PLANTING" 0 ((2435.89717 1108.59729) (2484.91731 1060.78201) (2530.16618 1055.81290) (2556.56109 1063.34842)))
("SF_PLANTING" 0 ((2469.83382 1123.67930) (2450.98066 1122.47590) (2435.89717 1108.59729)))
("SF_PLANTING" 0 ((2473.60509 931.37161) (2458.52161 941.62817) (2439.66844 942.68382)))
("SF_PLANTING" 0 ((2447.20939 4008.29604) (2462.29287 4008.29604)))
("SF_PLANTING" 0 ((2507.54174 3914.02715) (2477.37557 3929.25837) (2458.52161 3951.73495)))
("SF_PLANTING" 0 ((2458.52161 3951.73495) (2462.29287 4008.29604)))
("SF_PLANTING" 0 ((2462.29287 4008.29604) (2481.14604 4009.49989) (2492.45826 4019.60826)))
("SF_PLANTING" 0 ((2469.83382 1229.26188) (2469.98213 1259.42590) (2474.80260 1274.36233) (2488.68778 1282.05034)))
("SF_PLANTING" 0 ((2469.83382 1123.67930) (2488.68778 1113.41799) (2503.77048 1112.36708)))
("SF_PLANTING" 0 ((2469.83382 1123.67930) (2484.91697 1141.32907) (2496.22952 1142.53394)))
("SF_PLANTING" 0 ((2473.60509 931.37161) (2481.13948 882.35294) (2481.13948 776.77319) (2477.37557 754.14876)
(2477.52387 686.27545) (2481.13948 663.65102) (2477.37557 614.62952)))
("SF_PLANTING" 0 ((2473.60509 931.37161) (2496.22952 935.14423) (2522.62443 931.37161)))
("SF_PLANTING" 0 ((2477.37557 4096.90758) (2496.22952 4095.02262)))
("SF_PLANTING" 0 ((2492.45826 4034.69038) (2481.30090 4049.77376) (2477.37557 4096.90758)))
("SF_PLANTING" 0 ((2477.37557 4096.90758) (2477.53043 4132.72353) (2484.91731 4140.27149)))
("SF_ARCHITECTURE" 0 ((2477.37557 2356.71165) (2496.22952 2356.71165)))
("SF_ARCHITECTURE" 0 ((2477.37557 2356.71165) (2473.75294 2345.39943) (2477.53043 2269.99140) (2484.91731 2262.44344)))
("SF_PLANTING" 0 ((2481.14604 599.54751) (2477.52387 588.23529) (2477.37557 554.29864)))
("SF_ARCHITECTURE" 0 ((2484.91731 4166.66708) (2484.91731 5192.30769)))
("SF_ARCHITECTURE" 0 ((2533.93665 5203.61991) (2503.77048 5203.46527) (2484.91731 5192.30769)))
("SF_PLANTING" 0 ((2484.91731 4166.66708) (2484.91731 4140.27149)))
("SF_PLANTING" 0 ((2484.91731 4140.27149) (2503.77070 4131.67998) (2503.77070 4125.18190) (2503.77070 4110.10600)
(2496.22952 4095.02262)))
("SF_ARCHITECTURE" 0 ((2484.91731 1331.07183) (2484.91731 2262.44344)))
("SF_ARCHITECTURE" 0 ((2496.22952 2356.71165) (2499.85170 2345.39943) (2499.84514 2281.29740) (2484.91731 2262.44344)))
("SF_PLANTING" 0 ((2488.68778 1282.05034) (2488.53948 1323.52251) (2484.91731 1331.07183)))
("SF_PLANTING" 0 ((2488.68778 1282.05034) (2507.54174 1282.05034)))
("SF_PLANTING" 0 ((2492.45826 4034.69038) (2492.45826 4019.60826)))
("SF_PLANTING" 0 ((2507.54174 4064.85713) (2504.66572 4049.77376) (2492.45826 4034.69038)))
("SF_PLANTING" 0 ((2507.54174 3970.58824) (2498.80238 4015.68247) (2492.45826 4019.60826)))
("SF_PLANTING" 0 ((2507.54174 4064.85713) (2506.33744 4083.71041) (2496.22952 4095.02262)))
("SF_ARCHITECTURE" 0 ((2533.93665 2360.48292) (2503.77738 2360.33518) (2496.22952 2356.71165)))
("SF_PLANTING" 0 ((2511.31222 1119.90950) (2496.22952 1142.53394)))
("SF_PLANTING" 0 ((2496.22952 1142.53394) (2500.15486 1149.02613) (2518.85396 1157.61595)))
("SF_PLANTING" 0 ((2662.14152 3797.13382) (2643.28835 3800.90498) (2530.16618 3800.89876) (2503.77048 3797.13382)))
("SF_PLANTING" 0 ((2507.54174 1104.82749) (2503.77048 1112.36708)))
("SF_PLANTING" 0 ((2511.31222 1119.90950) (2503.77048 1112.36708)))
("SF_PLANTING" 0 ((2533.93665 995.47511) (2503.77048 1018.09955)))
("SF_PLANTING" 0 ((2537.70735 4064.85713) (2507.54174 4064.85713)))
("SF_PLANTING" 0 ((2507.54174 3914.02715) (2507.54174 3891.40271)))
("SF_PLANTING" 0 ((2507.54174 3914.02715) (2522.63100 3931.68314) (2545.24887 3940.27432) (2560.33156 3940.42274)))
("SF_PLANTING" 0 ((2560.33156 3898.94378) (2541.47839 3891.55079) (2507.54174 3891.40271)))
("SF_PLANTING" 0 ((2507.54174 1282.05034) (2514.93484 1248.11369) (2518.85396 1199.09502)))
("SF_PLANTING" 0 ((2507.54174 1282.05034) (2537.70713 1304.67477)))
("SF_PLANTING" 0 ((2511.31222 1119.90950) (2526.39491 1119.90950)))
("SF_PLANTING" 0 ((2522.62443 1195.32523) (2522.62443 1199.09502) (2518.85396 1199.09502)))
("SF_PLANTING" 0 ((2522.62443 1195.32523) (2518.85396 1199.09502)))
("SF_PLANTING" 0 ((2526.39491 1119.90950) (2530.01765 1138.76414) (2518.85396 1157.61595)))
("SF_PLANTING" 0 ((2522.62443 1195.32523) (2519.00181 1187.77590) (2518.85396 1157.61595)))
("SF_PLANTING" 0 ((2522.62443 1195.32523) (2567.87330 1187.78281)))
("SF_PLANTING" 0 ((2522.62443 931.37161) (2541.47839 938.91403)))
("SF_PLANTING" 0 ((2526.39491 1119.90950) (2551.58631 1097.27885) (2556.56109 1063.34842)))
("SF_ARCHITECTURE" 0 ((2533.93665 5203.61991) (2571.64378 5203.61991)))
("SF_ARCHITECTURE" 0 ((2537.70735 4170.43699) (2537.70735 4306.18360) (2537.70735 4325.03812) (2533.93665 5203.61991)))
("SF_ARCHITECTURE" 0 ((2533.93665 2360.48292) (2571.64378 2360.48292)))
("SF_ARCHITECTURE" 0 ((2533.93665 2360.48292) (2533.93009 2198.34061) (2530.17274 2179.48744) (2533.93665 2134.23857)
(2533.78835 2088.98971) (2530.17274 2073.90622) (2530.31403 2002.26244) (2533.93665 1983.40848) (2533.78835 1930.61867)
(2530.17274 1915.53518) (2530.17274 1587.48020) (2533.93009 1568.62839) (2533.94321 1319.75962) (2537.70713
1304.67477)))
("SF_PLANTING" 0 ((2533.93665 995.47511) (2541.33009 961.53846) (2541.47839 938.91403)))
("SF_PLANTING" 0 ((2533.93665 995.47511) (2552.79061 1005.44163) (2575.41505 987.93269)))
("SF_PLANTING" 0 ((2571.64378 1308.44740) (2537.70713 1304.67477)))
("SF_PLANTING" 0 ((2537.70735 4170.43699) (2571.64400 4170.43699)))
("SF_PLANTING" 0 ((2537.70735 4170.43699) (2537.70735 4140.27149) (2537.70735 4125.18812) (2537.70735 4064.85713)))
("SF_PLANTING" 0 ((2537.70735 4064.85713) (2542.53439 4049.77376) (2564.10283 4027.14932)))
("SF_PLANTING" 0 ((2541.47839 938.91403) (2556.56109 935.29129) (2643.28835 935.13733) (2662.14152 931.37851)
(2756.41052 935.14423)))
("SF_PLANTING" 0 ((2560.33156 4008.29604) (2545.24887 4000.75373)))
("SF_PLANTING" 0 ((2556.56109 1063.34842) (2601.80995 1063.49615) (2613.12217 1067.11821)))
("SF_PLANTING" 0 ((2560.33156 4008.29604) (2567.72500 3989.44152) (2564.10283 3951.73495)))
("SF_PLANTING" 0 ((2560.33156 4008.29604) (2564.10283 4019.60826)))
("SF_PLANTING" 0 ((2560.33156 3898.94378) (2560.33156 3940.42274)))
("SF_PLANTING" 0 ((2564.10283 3951.73495) (2560.33156 3940.42274)))
("SF_PLANTING" 0 ((2624.43439 3891.40271) (2613.12217 3887.77998) (2579.18552 3887.78654) (2560.33156 3898.94378)))
("SF_PLANTING" 0 ((2564.10283 4019.60826) (2564.10283 4027.14932)))
("SF_PLANTING" 0 ((2564.10283 4027.14932) (2571.64400 4038.46154) (2571.64400 4136.50034) (2571.64400 4151.58371)
(2571.64400 4170.43699)))
("SF_PLANTING" 0 ((2564.10283 4019.60826) (2605.58043 4038.46154)))
("SF_PLANTING" 0 ((2594.26821 3955.50486) (2564.10283 3951.73495)))
("SF_PLANTING" 0 ((2586.72726 1187.78281) (2567.87330 1187.78281)))
("SF_PLANTING" 0 ((2571.64378 1308.44740) (2567.87330 1187.78281)))
("SF_PLANTING" 0 ((2594.26821 1123.67930) (2575.56290 1128.65532) (2567.87330 1138.76414)))
("SF_ARCHITECTURE" 0 ((2613.12217 5203.61991) (2571.64378 5203.61991)))
("SF_ARCHITECTURE" 0 ((2571.64378 5203.61991) (2571.64400 4196.83258) (2571.64400 4170.43699)))
("SF_ARCHITECTURE" 0 ((2613.12217 2360.48292) (2571.64378 2360.48292)))
("SF_ARCHITECTURE" 0 ((2571.64378 1308.44740) (2567.87330 1372.54808) (2571.64378 2360.48292)))
("SF_PLANTING" 0 ((2586.72726 1187.78281) (2587.78326 1168.92817) (2601.80995 1138.76414)))
("SF_PLANTING" 0 ((2586.72726 1187.78281) (2594.12726 1188.98767) (2598.93405 1195.33009) (2610.40113 1244.34389)
(2617.94253 1259.27262) (2624.43439 1263.19853)))
("SF_PLANTING" 0 ((2594.26821 3955.50486) (2624.43439 3906.48609)))
("SF_PLANTING" 0 ((2598.03948 3963.04717) (2594.26821 3955.50486)))
("SF_PLANTING" 0 ((2594.26821 1123.67930) (2595.47251 1108.59729) (2609.35170 1097.28507)))
("SF_PLANTING" 0 ((2594.26821 1123.67930) (2601.80995 1138.76414)))
("SF_PLANTING" 0 ((2598.03948 3963.04717) (2605.73529 3985.52319) (2624.43439 3993.21267)))
("SF_PLANTING" 0 ((2598.03948 3963.04717) (2620.65701 3963.19502) (2628.20486 3966.81708)))
("SF_PLANTING" 0 ((2601.80995 1138.76414) (2620.66391 1138.76414)))
("SF_PLANTING" 0 ((2613.12217 4038.46154) (2605.58043 4038.46154)))
("SF_PLANTING" 0 ((2605.58043 4038.46154) (2614.31335 4083.71041) (2628.20486 4102.56369)))
("SF_PLANTING" 0 ((2609.35170 1097.28507) (2613.12217 1067.11821)))
("SF_PLANTING" 0 ((2609.35170 1097.28507) (2619.45962 1108.59729) (2624.43439 1131.22172)))
("SF_ARCHITECTURE" 0 ((2643.28835 5203.61991) (2613.12217 5203.61991)))
("SF_ARCHITECTURE" 0 ((2613.12217 5203.61991) (2617.04751 5082.95667) (2628.20486 5067.87330)))
("SF_ARCHITECTURE" 0 ((2613.12217 2360.48292) (2639.51708 2360.48292)))
("SF_ARCHITECTURE" 0 ((2613.12217 2360.48292) (2613.12217 2107.84287) (2613.12217 2085.21844) (2613.12217 1987.17975)
(2624.43439 1975.86753)))
("SF_PLANTING" 0 ((2662.14152 1059.57862) (2628.20486 1059.72636) (2613.12217 1067.11821)))
("SF_PLANTING" 0 ((2620.66391 1138.76414) (2624.43439 1131.22172)))
("SF_PLANTING" 0 ((2620.66391 1138.76414) (2625.63857 1153.84615) (2647.05882 1187.78281)))
("SF_ARCHITECTURE" 0 ((2624.43439 5663.65000) (2654.60057 5663.65000)))
("SF_PLANTING" 0 ((2624.43439 3993.21267) (2628.20486 3966.81708)))
("SF_PLANTING" 0 ((2643.28835 4004.52489) (2631.98269 4003.32070) (2624.43439 3993.21267)))
("SF_PLANTING" 0 ((2624.43439 3891.40271) (2624.43439 3906.48609)))
("SF_PLANTING" 0 ((2658.37104 3947.96380) (2650.67489 3925.48744) (2624.43439 3906.48609)))
("SF_PLANTING" 0 ((2624.43439 3891.40271) (2647.05882 3887.63156) (2680.98891 3887.77998) (2688.53722 3891.40271)))
("SF_ARCHITECTURE" 0 ((2624.43439 1975.86753) (2624.43439 1862.74536)))
("SF_ARCHITECTURE" 0 ((2624.43439 1975.86753) (2639.51731 1990.95023) (2639.51708 2360.48292)))
("SF_ARCHITECTURE" 0 ((2628.20486 1817.49717) (2639.51731 1828.80871) (2639.51731 1847.66188) (2639.51731 1855.19672)
(2624.43439 1862.74536)))
("SF_ARCHITECTURE" 0 ((2628.20486 1817.49717) (2613.12217 1825.04434) (2613.12217 1832.57919) (2613.12217 1851.43314)
(2624.43439 1862.74536)))
("SF_PLANTING" 0 ((2624.43439 1263.19853) (2624.43439 1278.28054)))
("SF_PLANTING" 0 ((2628.20486 1346.15385) (2617.04751 1338.60656) (2613.27704 1331.07183) (2613.27048 1300.90498)
(2624.43439 1278.28054)))
("SF_PLANTING" 0 ((2624.43439 1278.28054) (2638.46109 1293.36256) (2647.05882 1315.98699)))
("SF_PLANTING" 0 ((2650.82930 1240.57410) (2624.43439 1263.19853)))
("SF_PLANTING" 0 ((2686.65158 1127.45192) (2658.37104 1123.82771) (2624.43439 1131.22172)))
("SF_PLANTING" 0 ((2662.14152 6881.59853) (2639.51742 6873.00113) (2628.20486 6862.74536)))
("SF_ARCHITECTURE" 0 ((2628.20486 4102.56369) (2628.20486 5067.87330)))
("SF_ARCHITECTURE" 0 ((2643.28835 5203.61991) (2639.36267 5082.95667) (2628.20486 5067.87330)))
("SF_PLANTING" 0 ((2684.76595 4113.87590) (2647.05882 4102.71210) (2628.20486 4102.56369)))
("SF_PLANTING" 0 ((2658.37104 3947.96380) (2643.28835 3961.99050) (2628.20486 3966.81708)))
("SF_ARCHITECTURE" 0 ((2628.20486 1346.15385) (2628.19830 1546.00396) (2624.43439 1568.62839) (2628.20486 1817.49717)))
("SF_PLANTING" 0 ((2628.20486 1346.15385) (2642.08405 1334.84163) (2647.05882 1315.98699)))
("SF_PLANTING" 0 ((2631.97613 991.70532) (2730.01482 991.71018) (2741.32704 995.47511)))
("SF_PLANTING" 0 ((2639.51708 6919.30645) (2707.39038 6934.38914)))
("SF_ARCHITECTURE" 0 ((2684.76595 1315.98699) (2684.75939 2115.38462) (2680.99548 2138.00905) (2684.75939 2187.02839)
(2684.61810 2345.39943) (2677.07670 2359.27873) (2639.51708 2360.48292)))
("SF_ARCHITECTURE" 0 ((2643.28835 5203.61991) (2677.21810 5202.41538) (2684.75939 5188.53654) (2684.76595 4128.95928)))
("SF_PLANTING" 0 ((2643.28835 4004.52489) (2643.28835 4015.83710)))
("SF_PLANTING" 0 ((2688.53722 4000.75373) (2650.83620 4000.90215) (2643.28835 4004.52489)))
("SF_PLANTING" 0 ((2647.05882 4042.23269) (2658.37760 4056.25939) (2684.76595 4064.85713)))
("SF_PLANTING" 0 ((2684.76595 1315.98699) (2647.05882 1315.98699)))
("SF_PLANTING" 0 ((2650.82930 1240.57410) (2647.05882 1187.78281)))
("SF_PLANTING" 0 ((2688.53722 1195.32523) (2665.91278 1187.93054) (2647.05882 1187.78281)))
("SF_PLANTING" 0 ((2650.82930 1240.57410) (2677.22500 1240.57410)))
("SF_PLANTING" 0 ((2688.53722 3949.84876) (2658.37104 3947.96380)))
("SF_PLANTING" 0 ((2662.14152 1082.20305) (2662.14152 1059.57862)))
("SF_PLANTING" 0 ((2688.53722 1059.57862) (2662.14152 1059.57862)))
("SF_PLANTING" 0 ((2688.53722 1202.86482) (2682.19321 1210.41414) (2677.22500 1240.57410)))
("SF_PLANTING" 0 ((2688.53722 1278.28054) (2677.22500 1240.57410)))
("SF_PLANTING" 0 ((2684.76595 4128.95928) (2684.76595 4113.87590)))
("SF_PLANTING" 0 ((2771.49321 4113.87590) (2745.09830 4135.44491) (2733.78609 4140.11686) (2684.76595 4128.95928)))
("SF_PLANTING" 0 ((2684.76595 4113.87590) (2692.30113 4095.02262) (2684.76595 4064.85713)))
("SF_PLANTING" 0 ((2688.53722 4046.00260) (2684.76595 4064.85713)))
("SF_PLANTING" 0 ((2684.76595 1315.98699) (2688.53722 1278.28054)))
("SF_PLANTING" 0 ((2686.65158 1127.45192) (2699.84943 1093.51527)))
("SF_PLANTING" 0 ((2686.65158 1127.45192) (2685.82240 1142.52704) (2692.30769 1150.07636)))
("SF_PLANTING" 0 ((2686.65158 1127.45192) (2714.93213 1134.99152)))
("SF_PLANTING" 0 ((2688.53722 4000.75373) (2688.53722 4046.00260)))
("SF_PLANTING" 0 ((2771.49321 4113.87590) (2760.02613 4095.17070) (2711.16165 4054.74219) (2688.53722 4046.00260)))
("SF_PLANTING" 0 ((2688.53722 4000.75373) (2688.53722 3949.84876)))
("SF_PLANTING" 0 ((2688.53722 4000.75373) (2718.70260 4000.90871) (2730.01482 4012.06595)))
("SF_PLANTING" 0 ((2688.53722 3949.84876) (2688.53722 3891.40271)))
("SF_PLANTING" 0 ((2688.53722 3949.84876) (2714.93213 3951.73495)))
("SF_PLANTING" 0 ((2688.53722 3891.40271) (2711.16165 3884.00950) (2745.09140 3884.00950) (2752.63925 3887.63156)))
("SF_PLANTING" 0 ((2733.78609 1297.13518) (2714.93213 1283.25520) (2688.53722 1278.28054)))
("SF_PLANTING" 0 ((2688.53722 1195.32523) (2688.53722 1202.86482)))
("SF_PLANTING" 0 ((2794.11765 1259.42590) (2767.72274 1254.46505) (2707.39038 1207.83462) (2688.53722 1202.86482)))
("SF_PLANTING" 0 ((2688.53722 1195.32523) (2692.30769 1150.07636)))
("SF_PLANTING" 0 ((2748.86878 1059.57862) (2741.32048 1053.23416) (2707.39038 1052.18394) (2688.53722 1059.57862)))
("SF_PLANTING" 0 ((2699.84943 1093.51527) (2688.53722 1059.57862)))
("SF_PLANTING" 0 ((2714.93213 1150.07636) (2692.30769 1150.07636)))
("SF_PLANTING" 0 ((2696.07817 6885.36980) (2711.16165 6890.33801) (2722.47387 6899.24819) (2752.63925 6901.50848)
(2779.03495 6919.30645)))
("SF_PLANTING" 0 ((2699.84943 1093.51527) (2733.77952 1088.54548) (2740.27104 1082.19548) (2748.86878 1059.57862)))
("SF_PLANTING" 0 ((2714.93213 6787.33032) (2719.75905 6760.93541) (2727.30034 6745.85226) (2737.55656 6735.73744)
(2756.40362 6729.57149) (2763.79706 6719.45701) (2767.72274 6681.74989) (2767.71618 6568.62771) (2763.95147
6557.31550)))
("SF_PLANTING" 0 ((2771.49321 6847.66188) (2733.78609 6843.89796) (2684.76595 6847.50747) (2673.61516 6840.11403)
(2670.88778 6832.57919) (2688.68473 6794.87862) (2696.07851 6788.53462) (2714.93213 6787.33032)))
("SF_PLANTING" 0 ((2714.93213 6787.33032) (2730.01482 6791.10079) (2997.73756 6787.33032)))
("SF_PLANTING" 0 ((2714.93213 3951.73495) (2719.75939 3940.42206) (2747.67104 3906.48609) (2752.63925 3887.63156)))
("SF_PLANTING" 0 ((2714.93213 3951.73495) (2722.48043 3961.84932) (2737.55656 3966.66923) (2752.48484 3965.61980)
(2756.41052 3959.27602)))
("SF_PLANTING" 0 ((2714.93213 1150.07636) (2714.93213 1134.99152)))
("SF_PLANTING" 0 ((2714.93213 1150.07636) (2733.78609 1157.61595)))
("SF_PLANTING" 0 ((2748.86878 1123.67930) (2714.93213 1134.99152)))
("SF_PLANTING" 0 ((2745.09830 4117.64706) (2722.47387 4102.56369)))
("SF_PLANTING" 0 ((2733.78609 1297.13518) (2745.09830 1289.74740) (2794.11765 1293.36256)))
("SF_PLANTING" 0 ((2733.78609 1297.13518) (2741.32704 1308.44740) (2745.09830 1308.44740)))
("SF_PLANTING" 0 ((2748.86878 1150.07636) (2733.78609 1157.61595)))
("SF_PLANTING" 0 ((2794.11765 1180.24038) (2763.95147 1184.00611) (2745.09830 1179.04321) (2734.99038 1168.92817)
(2733.78609 1157.61595)))
("SF_ARCHITECTURE" 0 ((2737.55656 1662.89593) (2741.32704 1670.43835)))
("SF_PLANTING" 0 ((2812.97161 7013.57466) (2745.09830 7054.00317) (2730.01482 7058.67523) (2711.46425 7057.61923)
(2715.08699 7039.96957) (2741.32704 7017.34514)))
("SF_PLANTING" 0 ((2741.32704 6941.93088) (2752.63959 6940.73314) (2779.03495 6919.30645)))
("SF_ARCHITECTURE" 0 ((2741.32704 4800.15124) (2741.32704 4807.69231)))
("SF_ARCHITECTURE" 0 ((2741.32704 4483.40916) (2741.32704 4475.86686)))
("SF_ARCHITECTURE" 0 ((2741.32704 4453.24242) (2741.32704 4445.70136)))
("SF_PLANTING" 0 ((2794.11765 1150.07636) (2748.86878 1150.07636)))
("SF_PLANTING" 0 ((2748.86878 1150.07636) (2748.86878 1123.67930)))
("SF_PLANTING" 0 ((2790.34717 1112.36708) (2760.18100 1117.19536) (2748.86878 1123.67930)))
("SF_PLANTING" 0 ((2790.34717 1059.57862) (2748.86878 1059.57862)))
("SF_PLANTING" 0 ((2756.41052 3959.27602) (2752.63925 3947.96380)))
("SF_PLANTING" 0 ((2752.63925 3887.63156) (2760.18756 3884.00950) (2790.34717 3883.86165)))
("SF_PLANTING" 0 ((2786.57590 3959.27602) (2756.41052 3959.27602)))
("SF_PLANTING" 0 ((2760.18100 6994.72070) (2786.57590 6969.38179) (2812.97161 6960.78405)))
("SF_PLANTING" 0 ((2763.95147 6481.90045) (2767.72274 6527.14932) (2763.95147 6557.31550)))
("SF_PLANTING" 0 ((2763.95147 6481.90045) (2797.88835 6478.12964)))
("SF_PLANTING" 0 ((2771.49321 6847.66188) (2775.26369 6874.05758)))
("SF_PLANTING" 0 ((2771.49321 6847.66188) (2812.97161 6847.81674) (2831.82477 6858.97410)))
("SF_PLANTING" 0 ((2771.49321 4113.87590) (2790.34695 4113.87590)))
("SF_PLANTING" 0 ((2771.49321 935.14423) (2790.34717 935.14423)))
("SF_PLANTING" 0 ((2803.54423 6915.53518) (2779.03495 6919.30645)))
("SF_PLANTING" 0 ((2786.57590 3959.27602) (2790.19887 3940.42274) (2790.34717 3883.86165)))
("SF_PLANTING" 0 ((2786.57590 3959.27602) (2790.34695 3981.90045) (2790.34695 4091.25147) (2790.34695 4113.87590)))
("SF_ARCHITECTURE" 0 ((2790.34695 4113.87590) (2790.34695 4132.73043) (2794.11765 5471.34197) (2794.11765 5490.19649)
(2794.11765 5595.77636) (2790.34717 5607.08903)))
("SF_ARCHITECTURE" 0 ((2790.34717 5746.60633) (2794.11765 5731.52330) (2790.34717 5682.50385) (2794.11109 5625.94276)
(2790.34717 5607.08903)))
("SF_ARCHITECTURE" 0 ((2797.88835 6195.32421) (2797.88835 6168.92919) (2797.88835 6150.07534) (2794.11109 5761.68937)
(2790.34717 5746.60633)))
("SF_PLANTING" 0 ((2790.34717 3797.13382) (2790.34717 3883.86165)))
("SF_ARCHITECTURE" 0 ((3242.83552 3797.13382) (3216.44050 3793.36391) (3159.87941 3797.13382) (3084.46448 3796.98597)
(3065.61086 3793.36391) (2929.86425 3793.37014) (2877.07364 3797.12760) (2861.99095 3793.51176) (2809.20034 3793.37014)
(2790.34717 3797.13382)))
("SF_PLANTING" 0 ((2794.11765 3582.20238) (2780.23925 3593.51459) (2778.88665 3638.76278) (2759.27251 3699.09502)
(2748.86222 3711.30238) (2726.25090 3715.38224) (2718.70916 3729.26052) (2718.85747 3785.81538) (2722.62828 3792.15916)
(2779.03462 3793.51176) (2790.34717 3797.13382)))
("SF_PLANTING" 0 ((2790.34717 1112.36708) (2794.11765 1085.97285) (2790.34717 1059.57862)))
("SF_PLANTING" 0 ((2790.34717 1112.36708) (2794.11765 1150.07636)))
("SF_PLANTING" 0 ((2790.34717 1059.57862) (2794.11765 1040.72398) (2794.11109 950.22624) (2790.34717 935.14423)))
("SF_PLANTING" 0 ((2801.65939 180.99548) (2801.65283 550.52885) (2794.12421 607.08993) (2794.11109 923.83201)
(2790.34717 935.14423)))
("SF_PLANTING" 0 ((2794.11765 3582.20238) (2797.88812 3012.82025)))
("SF_PLANTING" 0 ((2794.11765 3582.20238) (2805.42986 3589.74333)))
("SF_ARCHITECTURE" 0 ((2794.11765 2812.97161) (2797.88812 2790.34717) (2794.12421 2756.41029) (2794.11765 2417.04400)
(2794.11765 2398.19005) (2790.35373 1372.54808) (2793.96934 1357.46606) (2794.11765 1293.36256)))
("SF_ARCHITECTURE" 0 ((2794.11765 2812.97161) (2801.65283 2828.05430) (2801.65283 2997.73756) (2797.88812 3012.82025)))
("SF_PLANTING" 0 ((2794.11765 1259.42590) (2794.11765 1293.36256)))
("SF_PLANTING" 0 ((2794.11765 1259.42590) (2797.88812 1214.17704) (2794.11765 1180.24038)))
("SF_PLANTING" 0 ((2794.11765 1180.24038) (2794.11765 1150.07636)))
("SF_PLANTING" 0 ((2797.88835 6195.32421) (2797.88835 6210.40724) (2797.88835 6478.12964)))
("SF_PLANTING" 0 ((2797.88835 6478.12964) (2820.51256 6481.89389) (3046.75724 6481.90045)))
("SF_ARCHITECTURE" 0 ((2801.65939 180.99548) (2801.65939 -3.77070)))
("SF_ARCHITECTURE" 0 ((2861.99095 -3.77070) (2824.28382 -3.77070) (2801.65939 -3.77070)))
("SF_PLANTING" 0 ((2805.42986 6900.45249) (2801.65939 6904.22296) (2803.54423 6915.53518)))
("SF_PLANTING" 0 ((2816.74208 6941.93088) (2803.54423 6915.53518)))
("SF_PLANTING" 0 ((2835.59604 6934.38914) (2824.27726 6920.36244) (2803.54423 6915.53518)))
("SF_PLANTING" 0 ((2820.51256 7013.57466) (2812.97161 7013.57466)))
("SF_PLANTING" 0 ((2820.51256 6987.17975) (2813.33314 6991.17081) (2812.97161 7013.57466)))
("SF_PLANTING" 0 ((2816.74208 6941.93088) (2812.97161 6960.78405)))
("SF_PLANTING" 0 ((2820.51256 6987.17975) (2812.97161 6960.78405)))
("SF_ARCHITECTURE" 0 ((3895.17387 3714.17839) (3880.09050 3717.94208) (2824.28382 3717.95520) (2812.97161 3721.71946)))
("SF_PLANTING" 0 ((2835.59604 6934.38914) (2828.04774 6940.73314) (2816.74208 6941.93088)))
("SF_PLANTING" 0 ((2816.74208 6734.53971) (2963.80090 6734.54627) (2978.88360 6738.01471) (2990.19615 6734.53971)))
("SF_PLANTING" 0 ((2831.82477 6987.17975) (2826.86312 7006.02636) (2820.51256 7013.57466)))
("SF_PLANTING" 0 ((2820.51256 7013.57466) (2824.12896 7024.88688) (2810.55294 7077.52262) (2828.05430 7081.29966)
(2899.69808 7039.82172) (2921.12534 7013.57466) (2937.56029 6979.79287) (2960.03009 6964.55532)))
("SF_PLANTING" 0 ((2831.82477 6987.17975) (2820.51256 6987.17975)))
("SF_PLANTING" 0 ((2831.82477 6987.17975) (2849.62274 6975.86063) (2861.99095 6941.93088)))
("SF_PLANTING" 0 ((2961.91561 6872.17195) (2948.72127 6860.17534) (2903.46900 6847.81018) (2846.90826 6847.81674)
(2831.82477 6858.97410)))
("SF_PLANTING" 0 ((2854.44921 6892.91075) (2840.42251 6877.82149) (2831.82477 6858.97410)))
("SF_PLANTING" 0 ((2835.59604 6934.38914) (2843.13699 6934.38914)))
("SF_ARCHITECTURE" 0 ((2835.59604 3646.30509) (2846.90826 3650.06878) (3929.10984 3650.08190) (3940.42274 3653.84615)))
("SF_PLANTING" 0 ((2858.22048 230.01414) (2835.59604 233.78676)))
("SF_PLANTING" 0 ((2839.36652 324.28450) (2858.22048 323.07964) (2884.60882 302.85724) (2892.15679 301.66007)))
("SF_PLANTING" 0 ((2854.44921 6892.91075) (2850.53043 6919.30645) (2843.13699 6934.38914)))
("SF_PLANTING" 0 ((2861.99095 6941.93088) (2843.13699 6934.38914)))
("SF_ARCHITECTURE" 0 ((4038.46154 3585.97285) (3947.96380 3585.97907) (3925.33937 3589.74333) (3774.50973 3589.73710)
(3751.88529 3585.97285) (3668.92919 3585.97907) (3650.07534 3589.74355) (3088.23529 3589.74355) (3069.38167 3585.97975)
(3046.75724 3589.73710) (2854.44955 3589.73710) (2843.13699 3585.97285)))
("SF_PLANTING" 0 ((2843.13699 444.94627) (2880.69661 411.00962) (2932.43756 350.67873) (2956.10486 301.66007)
(2959.86878 275.26301) (2948.71787 260.18100)))
("SF_ARCHITECTURE" 0 ((2846.90826 5829.56267) (3174.96222 5829.56923) (3197.58665 5833.33326) (3235.29412 5829.56267)))
("SF_MASONRY_AND_ARCH" 0 ((2846.90826 1866.51584) (2869.53269 1866.51584)))
("SF_MASONRY_AND_ARCH" 0 ((2899.69842 1176.47059) (2846.90826 1172.70079)))
("SF_ARCHITECTURE" 0 ((2850.67873 5795.62602) (2861.99095 5799.39005) (2914.78122 5799.24842) (2929.86425 5795.63258)
(3190.04525 5795.62602) (3205.12828 5795.62590)))
("SF_MASONRY_AND_ARCH" 0 ((2850.67873 3465.30894) (2858.22704 3468.93247) (2941.17647 3469.23484) (2956.25950
3476.46652) (3016.59118 3476.62115)))
("SF_MASONRY_AND_ARCH" 0 ((2933.63507 3355.95803) (2850.67873 3355.95803)))
("SF_MASONRY_AND_ARCH" 0 ((2899.69842 2745.09830) (2892.15023 2748.72104) (2850.67873 2748.86878)))
("SF_MASONRY_AND_ARCH" 0 ((2854.44921 2677.22500) (2850.67873 2684.76595)))
("SF_MASONRY_AND_ARCH" 0 ((2850.67873 2669.68326) (2854.44921 2677.22500)))
("SF_MASONRY_AND_ARCH" 0 ((2850.67873 2496.22952) (2861.99095 2499.99378) (3073.15226 2500.00000) (3080.69389
2503.77048) (3156.10860 2500.00622) (3171.19163 2503.62274) (3242.83552 2503.91821) (3254.14774 2507.38710) (3269.23077
2503.91821) (3322.02104 2503.77670) (3344.64548 2507.54174)))
("SF_MASONRY_AND_ARCH" 0 ((2850.67873 2383.10735) (2918.55204 2382.95271) (2933.63507 2371.79514)))
("SF_MASONRY_AND_ARCH" 0 ((2918.55204 2281.29740) (2903.46900 2284.92014) (2858.22704 2284.91324) (2850.67873
2277.52613)))
("SF_MASONRY_AND_ARCH" 0 ((2911.01063 2228.50679) (2899.69808 2235.89389) (2858.22704 2235.90079) (2850.67873
2232.27726)))
("SF_MASONRY_AND_ARCH" 0 ((2850.67873 1957.01357) (2907.23982 1956.86584) (2926.09344 1953.24310) (2948.71787
1957.00735) (3084.46448 1957.16131) (3114.63054 1960.93869) (3129.71335 1970.89219) (3159.87941 1975.71290) (3178.73303
1972.10249) (3295.62602 1972.10249) (3314.47964 1975.71290) (3325.79186 1972.24400) (3359.72851 1975.57127) (3378.58213
1972.09627) (3427.60181 1975.86131) (3446.45543 1972.10939) (3465.30928 1975.86131) (3567.11267 1976.01527) (3574.66063
1979.63801)))
("SF_MASONRY_AND_ARCH" 0 ((2903.46900 1723.22681) (2902.26482 1730.62149) (2895.92104 1734.38575) (2865.76143
1738.30407) (2850.67873 1734.53903)))
("SF_MASONRY_AND_ARCH" 0 ((3141.02557 1674.20814) (3122.17195 1670.44321) (2922.32285 1670.44321) (2861.99095
1677.97172) (2854.60407 1676.78077) (2850.67873 1670.43835)))
("SF_MASONRY_AND_ARCH" 0 ((2850.67873 1455.50622) (2858.22704 1459.12828) (2933.63507 1459.42376) (2948.71787
1463.04095) (3027.90339 1459.27602)))
("SF_MASONRY_AND_ARCH" 0 ((2892.15679 1391.40271) (2877.07364 1394.87704) (2861.99095 1391.56357) (2850.67873
1398.94514)))
("SF_PLANTING" 0 ((2854.44921 6892.91075) (2865.76143 6892.91075) (2869.53269 6896.68201)))
("SF_MASONRY_AND_ARCH" 0 ((2854.44921 3276.77251) (2858.37489 3270.42873) (2933.63507 3269.37851) (2952.48869
3273.00124) (3039.21561 3272.99502) (3061.84005 3269.23767) (3095.77670 3273.00124) (3114.63054 3269.37851) (3178.73303
3269.08303) (3227.75271 3257.91855)))
("SF_MASONRY_AND_ARCH" 0 ((2963.80090 3190.04525) (2944.94729 3193.80950) (2854.44921 3193.81572)))
("SF_MASONRY_AND_ARCH" 0 ((2895.92760 2677.22500) (2854.44921 2677.22500)))
("SF_MASONRY_AND_ARCH" 0 ((2903.46900 2643.28835) (2895.77296 2625.63857) (2854.44921 2624.43439)))
("SF_MASONRY_AND_ARCH" 0 ((3257.91855 2575.41505) (3171.19163 2575.40882) (3156.10860 2571.94005) (3144.79638
2575.26731) (3092.00611 2575.40882) (3069.38167 2571.64378) (3035.44502 2575.40882) (3020.36199 2571.94005) (2960.18473
2576.61912) (2955.05509 2594.11357) (2948.71131 2597.88484) (2869.53269 2594.26821) (2854.44921 2598.03948)))
("SF_MASONRY_AND_ARCH" 0 ((2978.88394 1610.10464) (2967.57138 1606.34106) (2854.44921 1606.33484)))
("SF_MASONRY_AND_ARCH" 0 ((2854.44921 1025.64197) (2914.78122 1025.78903) (2926.09344 1029.41176)))
("SF_MASONRY_AND_ARCH" 0 ((3099.54751 984.16290) (3091.85147 962.74333) (3061.84005 957.91572) (2993.96674 957.91572)
(2967.57172 961.53846) (2907.23982 957.77353) (2869.53269 961.53846) (2854.44921 957.76867)))
("SF_PLANTING" 0 ((2854.44921 784.31278) (2865.76176 788.07851) (2918.55204 787.93699) (2937.40566 784.31278)
(3031.67421 788.07851) (3050.52783 784.31968) (3148.56719 784.16572) (3182.50385 776.77319)))
("SF_PLANTING" 0 ((2877.07364 588.23529) (2854.44921 580.69287)))
("SF_PLANTING" 0 ((2858.22048 7021.11640) (2907.09174 6964.55532) (2918.55204 6945.70136)))
("SF_MASONRY_AND_ARCH" 0 ((2858.22048 2971.34265) (2869.53269 2967.57760) (3020.36199 2967.57760) (3035.44502
2971.04638) (3046.75068 2967.87387) (3054.29864 2975.11312)))
("SF_MASONRY_AND_ARCH" 0 ((3054.29864 2903.46934) (3016.59118 2899.69808) (2869.53269 2903.46312) (2858.22048
2899.69808)))
("SF_MASONRY_AND_ARCH" 0 ((3122.17195 2816.74208) (3103.31833 2820.50633) (2911.01063 2820.51878) (2892.15679
2824.27760) (2865.76833 2824.13609) (2858.22048 2820.51256)))
("SF_PLANTING" 0 ((2941.17647 720.21120) (2858.22048 720.21120)))
("SF_PLANTING" 0 ((2858.22048 230.01414) (2854.59751 203.61991) (2861.99095 184.76527)))
("SF_PLANTING" 0 ((2858.22048 230.01414) (2869.53269 233.78586) (2926.09344 233.78586) (2948.71787 248.86878)))
("SF_PLANTING" 0 ((2914.78122 6926.84740) (2884.61538 6928.05170) (2861.99095 6941.93088)))
("SF_MASONRY_AND_ARCH" 0 ((3344.64548 3046.75690) (3329.56267 3050.52127) (3306.93824 3046.76312) (3212.66968
3046.76312) (3190.04525 3050.52127) (3174.96222 3046.90464) (3095.77670 3046.75690) (3076.92308 3050.37353) (3058.06946
3046.77002) (3042.98643 3050.38043) (3020.36199 3047.05317) (2971.34231 3050.52817) (2944.94729 3046.76312) (2861.99095
3046.75690)))
("SF_MASONRY_AND_ARCH" 0 ((2899.69842 1266.96833) (2861.99095 1266.96833)))
("SF_ARCHITECTURE" 0 ((2861.99095 184.76527) (7846.90894 184.76527)))
("SF_ARCHITECTURE" 0 ((2861.99095 -3.77070) (2861.99095 184.76527)))
("SF_ARCHITECTURE" 0 ((2861.99095 -3.77070) (2880.84491 -3.77070) (2907.23982 -3.77070) (3212.66968 -3.77070)
(3235.29412 -3.77070) (3325.79186 -3.77070) (3348.41629 -3.77070) (3404.97738 -3.77070) (4615.38462 -3.77070)
(4638.00905 -3.77070) (4739.81900 -3.77070) (4762.44344 -3.77070) (4822.77568 -3.77070) (4841.62896 -3.77070)
(4943.43891 -3.77070) (4966.06335 -3.77070) (5282.80543 -3.77070) (5297.88880 -3.77070) (5312.97093 -3.77070)
(5463.80090 -3.77070) (5478.88428 -3.77070) (5493.96640 -3.77070) (6225.48993 -3.77070) (6248.11437 -3.77070)
(7846.90894 -3.77070)))
("SF_PLANTING" 0 ((2907.23982 320.51188) (2877.07364 365.76075)))
("SF_PLANTING" 0 ((2892.15679 301.66007) (2914.78156 271.64163) (2926.09344 265.00792) (2941.17647 263.95079)))
("SF_PLANTING" 0 ((2907.23982 320.51188) (2892.15679 301.66007)))
("SF_MASONRY_AND_ARCH" 0 ((2899.69842 3001.50803) (2895.92760 2993.96708)))
("SF_MASONRY_AND_ARCH" 0 ((2907.23982 1319.75962) (2895.92760 1319.75962)))
("SF_MASONRY_AND_ARCH" 0 ((2907.23982 3525.64129) (2899.69842 3518.09955)))
("SF_MASONRY_AND_ARCH" 0 ((2899.69842 2745.09830) (2899.69842 2703.61991)))
("SF_MASONRY_AND_ARCH" 0 ((2899.69842 2745.09830) (2907.24638 2748.72104) (2960.03009 2752.63303) (3035.44502
2752.49152) (3046.75724 2749.17115) (3080.69389 2760.03326) (3110.85973 2761.85260) (3220.21109 2756.41052)))
("SF_MASONRY_AND_ARCH" 0 ((2911.01063 2062.59400) (2899.69842 2058.82353)))
("SF_MASONRY_AND_ARCH" 0 ((2903.46900 1225.48925) (2899.69842 1266.96833)))
("SF_MASONRY_AND_ARCH" 0 ((2907.23982 1274.51075) (2907.23982 1270.73812) (2899.69842 1266.96833)))
("SF_MASONRY_AND_ARCH" 0 ((2899.69842 1176.47059) (2926.09344 1161.38857)))
("SF_MASONRY_AND_ARCH" 0 ((2899.69842 1176.47059) (2903.46900 1187.78281)))
("SF_PLANTING" 0 ((2899.69842 584.46550) (2918.55204 592.00509)))
("SF_MASONRY_AND_ARCH" 0 ((3050.52783 1376.32070) (3046.60260 1387.47760) (3039.21561 1391.24808) (2903.46900
1391.40271)))
("SF_MASONRY_AND_ARCH" 0 ((2907.23982 1274.51075) (2910.99751 1300.90498) (2907.23982 1319.75962)))
("SF_MASONRY_AND_ARCH" 0 ((2937.40566 1334.84163) (2907.23982 1319.75962)))
("SF_MASONRY_AND_ARCH" 0 ((2907.23982 1274.51075) (2926.09344 1270.89344) (2944.94729 1274.50385) (3144.79638
1274.51075)))
("SF_PLANTING" 0 ((2907.23982 426.09446) (2929.87081 399.69740) (2944.94729 388.38518)))
("SF_PLANTING" 0 ((2907.23982 320.51188) (2917.49604 316.58744) (2928.81448 297.88744) (2941.17647 263.95079)))
("SF_MASONRY_AND_ARCH" 0 ((2911.01063 2062.59400) (2926.09344 2055.05305)))
("SF_MASONRY_AND_ARCH" 0 ((2911.01063 2062.59400) (2911.15882 2081.44796) (2918.55204 2100.30192)))
("SF_MASONRY_AND_ARCH" 0 ((3133.48416 1858.97410) (3114.63054 1866.36120) (3095.77670 1862.75158) (2937.40566
1862.75158) (2911.01063 1870.28631)))
("SF_PLANTING" 0 ((2961.91561 6872.17195) (2922.47760 6911.76471) (2914.78122 6926.84740)))
("SF_PLANTING" 0 ((2914.78122 6926.84740) (2918.55204 6945.70136)))
("SF_MASONRY_AND_ARCH" 0 ((2914.78122 2115.38462) (2914.78122 2104.07240) (2918.55204 2100.30192)))
("SF_ARCHITECTURE" 0 ((3755.65611 8073.15238) (3736.80249 8073.15238) (2929.86425 8073.15238) (2918.55204 8073.15238)))
("SF_ARCHITECTURE" 0 ((2918.55204 8073.15238) (2923.52048 8039.21561) (2943.74287 8016.59129) (2949.92229 7963.80102)
(2960.02353 7953.69299) (2967.57172 7952.48869)))
("SF_ARCHITECTURE" 0 ((3755.65611 8073.15238) (3774.50973 8073.15238) (3785.66765 8088.23529) (3782.20611 8122.17195)
(3785.66765 8167.42070) (3774.50973 8178.57839) (2903.46934 8178.57839) (2892.31143 8167.42070) (2892.30486 8095.77670)
(2899.85317 8073.15238) (2918.55204 8073.15238)))
("SF_PLANTING" 0 ((2960.03009 6945.70136) (2948.71787 6941.94400) (2918.55204 6945.70136)))
("SF_MASONRY_AND_ARCH" 0 ((2918.55204 2281.29740) (2922.47760 2267.41810) (2948.71787 2262.44344) (2997.73756
2266.20769) (3069.38167 2266.06618) (3080.69389 2262.73959) (3095.47387 2270.13292) (3095.77670 2281.29740)))
("SF_MASONRY_AND_ARCH" 0 ((2918.55204 2281.29740) (2928.66007 2292.60962) (2931.06878 2315.08552) (2941.17647
2321.71867) (2952.48869 2322.77500)))
("SF_MASONRY_AND_ARCH" 0 ((3182.50385 2156.86278) (2922.47760 2155.66505) (2918.55204 2149.32127)))
("SF_MASONRY_AND_ARCH" 0 ((2978.88394 2100.30192) (2918.55204 2100.30192)))
("SF_MASONRY_AND_ARCH" 0 ((2926.09344 1161.38857) (2922.32285 1142.53394)))
("SF_MASONRY_AND_ARCH" 0 ((2922.32285 1082.20305) (2933.64163 1093.35995) (2975.11312 1093.51527)))
("SF_MASONRY_AND_ARCH" 0 ((2922.32285 1044.49378) (2926.09344 1029.41176)))
("SF_MASONRY_AND_ARCH" 0 ((2933.63507 3329.56233) (2926.09344 3329.56233)))
("SF_MASONRY_AND_ARCH" 0 ((2926.09344 1161.38857) (2948.71787 1168.92330) (3046.75724 1165.15837)))
("SF_MASONRY_AND_ARCH" 0 ((2986.42534 1029.41176) (2967.57172 1025.64197) (2926.09344 1029.41176)))
("SF_PLANTING" 0 ((2937.40566 7070.13575) (2929.86425 7073.90622)))
("SF_MASONRY_AND_ARCH" 0 ((2933.63507 3355.95803) (2933.63507 3329.56233)))
("SF_MASONRY_AND_ARCH" 0 ((2933.63507 3355.95803) (2937.39910 3378.58247) (2933.79638 3401.20690) (2941.18303
3411.46267) (2952.48869 3416.14118) (3024.13281 3416.28959)))
("SF_MASONRY_AND_ARCH" 0 ((2933.63507 3329.56233) (2956.25950 3325.79808) (3227.75271 3325.79186)))
("SF_MASONRY_AND_ARCH" 0 ((2933.63507 2371.79514) (2997.73756 2368.03699) (3012.82059 2371.64740) (3084.46448
2371.64050) (3103.31833 2364.26029) (3363.49932 2364.26029) (3386.12376 2375.41097) (3472.85068 2375.71403) (3503.01652
2383.09423) (3518.09955 2379.33609)))
("SF_MASONRY_AND_ARCH" 0 ((2933.63507 2360.48292) (2933.63507 2371.79514)))
("SF_MASONRY_AND_ARCH" 0 ((3318.25045 2654.60057) (3235.30068 2654.44593) (3228.80916 2650.67466) (3223.61980
2636.94457) (3208.89887 2632.12387) (2948.71821 2631.96991) (2937.40566 2628.20486)))
("SF_MASONRY_AND_ARCH" 0 ((2941.17647 1745.85124) (2933.63507 1749.62387) (2937.40566 1757.16346)))
("SF_MASONRY_AND_ARCH" 0 ((2937.40566 1334.84163) (2937.40566 1342.38405)))
("SF_MASONRY_AND_ARCH" 0 ((2937.40566 1334.84163) (3050.52783 1334.84163)))
("SF_MASONRY_AND_ARCH" 0 ((2941.17647 1809.95475) (2956.25950 1813.71968) (3122.16538 1813.87986) (3133.48416
1825.03744)))
("SF_PLANTING" 0 ((2941.17647 739.06391) (2941.17647 720.21120)))
("SF_PLANTING" 0 ((2941.17647 720.21120) (2967.56516 720.21120) (2975.11312 727.75170)))
("SF_PLANTING" 0 ((2941.17647 263.95079) (2948.71787 260.18100)))
("SF_PLANTING" 0 ((2944.94729 388.38518) (2944.94729 373.30317)))
("SF_PLANTING" 0 ((2944.94729 388.38518) (2956.25950 392.15781)))
("SF_PLANTING" 0 ((3061.84005 844.64649) (3009.04977 840.88767) (2967.57172 844.63959) (2948.71787 840.87387)))
("SF_PLANTING" 0 ((2948.71787 248.86878) (2948.71787 260.18100)))
("SF_PLANTING" 0 ((3046.75724 252.63857) (3035.44468 242.38348) (3012.82059 233.78586) (2993.96674 233.78586)
(2948.71787 248.86878)))
("SF_MASONRY_AND_ARCH" 0 ((2952.48869 2055.05305) (3016.59118 2055.05305)))
("SF_PLANTING" 0 ((2956.25950 399.69740) (2956.25950 392.15781)))
("SF_PLANTING" 0 ((2997.73756 271.49321) (2985.36900 320.51188) (2968.62783 365.76075) (2966.36765 384.60848)
(2956.25950 392.15781)))
("SF_PLANTING" 0 ((2960.03009 6964.55532) (2960.03009 6945.70136)))
("SF_PLANTING" 0 ((2960.03009 6964.55532) (2966.37421 6972.10317) (2967.57172 6990.95023)))
("SF_PLANTING" 0 ((2967.57172 6941.93088) (2960.03009 6945.70136)))
("SF_MASONRY_AND_ARCH" 0 ((2963.80090 3190.04525) (2960.03009 3174.96256)))
("SF_MASONRY_AND_ARCH" 0 ((2963.80090 3148.56686) (2960.03009 3156.10860)))
("SF_MASONRY_AND_ARCH" 0 ((2960.03009 3103.31799) (2978.88394 3110.85351) (3159.87941 3110.85351) (3182.50385
3107.09615) (3205.12828 3110.85973) (3272.99502 3107.23767) (3280.54299 3110.85973)))
("SF_PLANTING" 0 ((2961.91561 6872.17195) (2993.96674 6870.28631)))
("SF_PLANTING" 0 ((2961.91561 6872.17195) (2967.57172 6941.93088)))
("SF_PLANTING" 0 ((2963.80090 7047.51131) (2982.65452 7047.35645) (2997.58948 7038.92014) (3023.07647 7009.80419)
(3027.90339 6994.72070)))
("SF_PLANTING" 0 ((2963.80090 7047.51131) (2963.94898 7002.26244) (2967.57172 6990.95023)))
("SF_ARCHITECTURE" 0 ((2963.80090 7047.51131) (2967.57161 7616.89287)))
("SF_MASONRY_AND_ARCH" 0 ((3148.56719 3190.04525) (3095.77670 3189.89751) (3080.69389 3186.28167) (3058.06946
3190.03903) (2963.80090 3190.04525)))
("SF_PLANTING" 0 ((2967.57172 535.44400) (2963.80090 546.75622)))
("SF_ARCHITECTURE" 0 ((3687.78281 7616.89287) (2967.57161 7616.89287)))
("SF_ARCHITECTURE" 0 ((2967.57172 7658.37104) (2956.41425 7643.28812) (2967.57161 7616.89287)))
("SF_ARCHITECTURE" 0 ((3691.55362 7952.48869) (2967.57172 7952.48869)))
("SF_ARCHITECTURE" 0 ((2967.57172 7658.37104) (2967.57172 7952.48869)))
("SF_ARCHITECTURE" 0 ((2967.57172 7658.37104) (2986.42534 7654.60034) (3031.67421 7658.37104) (3623.68032 7658.36448)
(3672.69977 7654.60690) (3687.78281 7658.37104)))
("SF_PLANTING" 0 ((3003.39367 6977.75238) (2967.57172 6990.95023)))
("SF_PLANTING" 0 ((2967.57172 6941.93088) (2975.11312 6941.93088)))
("SF_PLANTING" 0 ((2971.34231 505.27998) (3011.76425 426.09446) (3012.82059 399.69740)))
("SF_PLANTING" 0 ((3016.59118 6907.99423) (2997.73756 6930.46380) (2975.11312 6941.93088)))
("SF_PLANTING" 0 ((3003.39367 6977.75238) (2975.11312 6941.93088)))
("SF_PLANTING" 0 ((3001.50837 392.15781) (2994.10826 396.08224) (2980.07500 418.55204) (2975.11312 441.17647)))
("SF_MASONRY_AND_ARCH" 0 ((2978.88394 1632.72907) (2978.88394 1610.10464)))
("SF_MASONRY_AND_ARCH" 0 ((3303.16742 1606.33484) (3193.81606 1606.32862) (3178.73303 1602.71833) (3122.17195
1606.32862) (3103.31833 1602.71833) (3016.59118 1610.09977) (2990.19615 1606.48948) (2978.88394 1610.10464)))
("SF_MASONRY_AND_ARCH" 0 ((3042.98643 2326.54627) (2986.42534 2326.54627)))
("SF_MASONRY_AND_ARCH" 0 ((2986.42534 1745.85124) (3027.90339 1745.70419) (3039.21561 1742.08145)))
("SF_MASONRY_AND_ARCH" 0 ((2986.42534 1093.51527) (3005.27896 1089.74955) (3069.38167 1092.31663) (3182.50385
1089.59559) (3197.58665 1085.97907) (3223.98190 1089.73778) (3303.16742 1089.89106) (3318.25045 1093.50769) (3340.87489
1089.74955) (3567.11923 1085.97907) (3593.51425 1093.36686) (3634.99253 1093.66233) (3691.55362 1104.67907) (3725.49027
1104.82749)))
("SF_MASONRY_AND_ARCH" 0 ((3054.29864 1025.64197) (3024.13281 1025.64197) (3016.59118 1025.64197) (2986.42534
1029.41176)))
("SF_MASONRY_AND_ARCH" 0 ((2986.42534 1029.41176) (2990.19615 1055.80600)))
("SF_ARCHITECTURE" 0 ((2990.19615 8016.59129) (3665.15837 8016.59129) (3687.78281 8016.59129)))
("SF_PLANTING" 0 ((3137.25498 6843.89140) (3111.69548 6869.77002) (3095.77670 6865.32466) (3069.38167 6845.09570)
(3035.44502 6843.89796) (3009.04977 6852.48914) (2993.96674 6870.28631)))
("SF_PLANTING" 0 ((2993.96674 6870.28631) (3011.76425 6892.91075) (3016.59118 6907.99423)))
("SF_PLANTING" 0 ((3005.27896 6787.33032) (2997.73756 6787.33032)))
("SF_PLANTING" 0 ((3005.27896 6787.33032) (3001.50837 6779.78857) (2997.73756 6787.33032)))
("SF_PLANTING" 0 ((3001.50837 392.15781) (3002.56448 350.67873) (3020.36199 316.74208)))
("SF_PLANTING" 0 ((3001.50837 392.15781) (3012.82059 399.69740)))
("SF_PLANTING" 0 ((3042.98643 6972.09627) (3031.52613 6961.98835) (3020.36855 6960.93914) (3003.39367 6977.75238)))
("SF_PLANTING" 0 ((3003.39367 6977.75238) (3027.90339 6994.72070)))
("SF_PLANTING" 0 ((3005.27896 6787.33032) (3016.59152 6794.71719) (3035.44502 6791.10079)))
("SF_PLANTING" 0 ((3009.04977 588.23529) (3012.82059 580.69287)))
("SF_PLANTING" 0 ((3024.13281 365.76075) (3023.08303 380.84559) (3012.82059 399.69740)))
("SF_PLANTING" 0 ((3016.59118 6907.99423) (3058.06946 6920.36244) (3080.69389 6938.15962)))
("SF_MASONRY_AND_ARCH" 0 ((3020.36199 2100.30192) (3069.38167 2096.53066) (3088.23529 2100.14729) (3118.40113
2096.67839) (3193.81606 2104.06618) (3254.14774 2100.30192)))
("SF_PLANTING" 0 ((3020.36199 316.74208) (3035.44502 316.74208)))
("SF_PLANTING" 0 ((3046.75724 252.63857) (3025.18925 282.80543) (3020.36199 316.74208)))
("SF_PLANTING" 0 ((3039.21561 6994.72070) (3027.90339 6994.72070)))
("SF_PLANTING" 0 ((3031.67421 6576.16867) (3054.29864 6598.79310)))
("SF_PLANTING" 0 ((3076.92308 7002.26244) (3086.12941 7032.42862) (3080.84208 7055.05305) (3080.54581 7111.61414)
(3075.71889 7130.46075) (3069.37511 7136.65011) (3055.50283 7126.69683) (3043.28258 7088.98971) (3045.70090 7058.82353)
(3035.44502 7043.74084)))
("SF_PLANTING" 0 ((3046.75724 6764.70588) (3035.44502 6791.10079)))
("SF_PLANTING" 0 ((3046.75724 6806.18428) (3035.44502 6791.10079)))
("SF_PLANTING" 0 ((3046.75724 6685.52036) (3035.44502 6662.89593)))
("SF_PLANTING" 0 ((3050.52783 316.74208) (3035.44502 316.74208)))
("SF_PLANTING" 0 ((3058.06946 354.44853) (3050.52127 353.24514) (3036.64921 339.36652) (3035.44502 316.74208)))
("SF_PLANTING" 0 ((3042.98643 6972.09627) (3039.21561 6994.72070)))
("SF_PLANTING" 0 ((3076.92308 7002.26244) (3054.29864 7002.11414) (3039.21561 6994.72070)))
("SF_MASONRY_AND_ARCH" 0 ((3186.27443 3416.28959) (3092.00611 3416.13495) (3076.92308 3412.52534) (3054.29864
3415.99344) (3039.21561 3412.51912)))
("SF_PLANTING" 0 ((3039.21561 414.78224) (3058.06946 403.47002)))
("SF_PLANTING" 0 ((3042.98643 6972.09627) (3058.06290 6964.40045) (3080.69389 6938.15962)))
("SF_PLANTING" 0 ((3046.75724 6730.76923) (3042.98643 6745.85192) (3046.75724 6764.70588)))
("SF_PLANTING" 0 ((3046.75724 6764.70588) (3061.84005 6765.76188) (3084.46448 6778.73914) (3107.08891 6783.55984)))
("SF_PLANTING" 0 ((3054.29864 6527.14932) (3046.90543 6512.06629) (3046.75724 6481.90045)))
("SF_PLANTING" 0 ((3046.75724 6481.90045) (3125.94276 6482.04853) (3141.02557 6485.67127)))
("SF_MASONRY_AND_ARCH" 0 ((3046.75724 3472.85068) (3069.38167 3480.38552) (3465.30928 3476.62115)))
("SF_MASONRY_AND_ARCH" 0 ((3046.75724 1346.15385) (3050.52783 1334.84163)))
("SF_PLANTING" 0 ((3046.75724 252.63857) (3054.29864 252.63857)))
("SF_MASONRY_AND_ARCH" 0 ((3050.52783 1334.84163) (3118.40113 1334.69389) (3137.25498 1331.07183) (3178.73303
1334.83541) (3310.70882 1334.83541) (3322.02104 1331.07183)))
("SF_PLANTING" 0 ((3061.84005 286.57523) (3055.48971 294.12455) (3050.52783 316.74208)))
("SF_PLANTING" 0 ((3058.06946 354.44853) (3057.92138 335.59672) (3050.52783 316.74208)))
("SF_MASONRY_AND_ARCH" 0 ((3054.29864 2903.46934) (3054.29864 2933.63473)))
("SF_MASONRY_AND_ARCH" 0 ((3054.29864 2903.46934) (3084.46448 2899.69808)))
("SF_PLANTING" 0 ((3156.10860 248.86878) (3141.02557 233.78586) (3122.17195 233.78586) (3073.15226 233.78586)
(3054.29864 252.63857)))
("SF_PLANTING" 0 ((3061.84005 286.57523) (3061.68529 267.72342) (3054.29864 252.63857)))
("SF_MASONRY_AND_ARCH" 0 ((3058.06946 3525.64129) (3058.06946 3533.18224) (3065.61086 3536.95351)))
("SF_MASONRY_AND_ARCH" 0 ((3295.62602 1447.96380) (3212.66968 1440.71833) (3197.58665 1444.18710) (3076.92308
1444.34729) (3058.06946 1459.27602)))
("SF_PLANTING" 0 ((3058.06946 354.44853) (3058.06946 403.47002)))
("SF_PLANTING" 0 ((3065.61086 426.09446) (3064.41324 411.01719) (3058.06946 403.47002)))
("SF_PLANTING" 0 ((3065.61086 426.09446) (3058.22421 441.17647) (3061.84005 456.25848)))
("SF_PLANTING" 0 ((3061.84005 286.57523) (3069.38824 287.78009) (3084.31629 301.66007) (3096.98077 331.82410)
(3107.08891 343.13631)))
("SF_PLANTING" 0 ((3065.61086 426.09446) (3084.45792 437.55373) (3099.55407 455.06131) (3114.63054 460.03111)))
("SF_MASONRY_AND_ARCH" 0 ((3069.38167 1489.44287) (3073.15226 1496.98247) (3076.92308 1496.98247)))
("SF_PLANTING" 0 ((3092.00611 6938.15962) (3099.24480 6953.24310) (3095.62195 6972.09627) (3076.92308 7002.26244)))
("SF_MASONRY_AND_ARCH" 0 ((3092.00611 2337.85848) (3087.17896 2322.92964) (3076.92308 2319.00452)))
("SF_MASONRY_AND_ARCH" 0 ((3076.92308 1165.15837) (3122.17195 1172.70079)))
("SF_PLANTING" 0 ((3092.00611 6938.15962) (3080.69389 6938.15962)))
("SF_PLANTING" 0 ((3137.25498 6685.52036) (3129.56516 6670.43767) (3114.63054 6659.28009) (3103.31833 6660.18145)
(3080.69389 6674.20814)))
("SF_PLANTING" 0 ((3080.69389 6564.85645) (3094.57907 6583.71041) (3094.57251 6610.10532) (3080.69389 6625.18880)))
("SF_PLANTING" 0 ((3265.45995 452.48869) (3265.31176 471.34333) (3256.86256 505.27998) (3208.75068 576.92308)
(3152.33778 629.56595) (3103.31833 662.45995) (3080.69389 667.42081)))
("SF_PLANTING" 0 ((3080.69389 667.42081) (3081.75034 652.33880) (3093.05566 633.48416) (3129.86143 588.23529)
(3159.73133 561.83348) (3181.45407 535.44400) (3215.39072 482.65554) (3220.21109 463.80090)))
("SF_PLANTING" 0 ((3112.74502 507.16346) (3113.42647 531.67421) (3070.43778 595.77771) (3036.50113 659.87839)
(3032.88529 682.34955) (3039.22217 686.12014) (3050.52783 685.21833) (3080.69389 667.42081)))
("SF_PLANTING" 0 ((3112.74502 507.16346) (3084.46448 524.13179)))
("SF_MASONRY_AND_ARCH" 0 ((3095.77670 2462.29287) (3088.23529 2473.60509)))
("SF_MASONRY_AND_ARCH" 0 ((3088.23529 1500.75509) (3107.08891 1504.51867) (3299.39661 1504.52489)))
("SF_MASONRY_AND_ARCH" 0 ((3088.23529 1025.64197) (3095.77670 1025.64197)))
("SF_PLANTING" 0 ((3092.00611 6938.15962) (3122.17195 6919.45430) (3156.10860 6915.54174) (3178.73303 6919.30645)))
("SF_MASONRY_AND_ARCH" 0 ((3092.00611 1542.23133) (3107.08891 1557.31618)))
("SF_MASONRY_AND_ARCH" 0 ((3099.54751 984.16290) (3095.77670 1025.64197)))
("SF_MASONRY_AND_ARCH" 0 ((3246.60633 1029.41176) (3231.52330 1033.17670) (3182.50385 1033.03450) (3167.42081
1029.41799) (3144.79638 1032.88609) (3095.77670 1025.64197)))
("SF_MASONRY_AND_ARCH" 0 ((3099.54751 984.16290) (3122.17195 984.16290)))
("SF_PLANTING" 0 ((3099.54751 893.66516) (3107.24355 853.24321) (3118.40113 848.56471) (3174.96222 848.41629)))
("SF_PLANTING" 0 ((3193.81606 716.43948) (3182.50351 719.91516) (3156.10860 720.21120) (3099.54751 720.21120)))
("SF_MASONRY_AND_ARCH" 0 ((3103.31833 2895.92760) (3114.63054 2899.69186) (3212.66968 2895.92760) (3227.75271
2899.69808)))
("SF_PLANTING" 0 ((3163.65000 6783.55984) (3107.08891 6783.55984)))
("SF_PLANTING" 0 ((3110.85973 6738.31097) (3107.08891 6783.55984)))
("SF_PLANTING" 0 ((3137.25498 6843.89140) (3117.50622 6821.26697) (3107.08891 6783.55984)))
("SF_MASONRY_AND_ARCH" 0 ((3107.08891 923.83201) (3182.50385 923.97907) (3201.35747 927.60181) (3435.14321 923.83201)))
("SF_PLANTING" 0 ((3122.17195 343.13631) (3107.08891 343.13631)))
("SF_PLANTING" 0 ((3137.25498 422.32183) (3115.68043 395.92760) (3107.08891 343.13631)))
("SF_PLANTING" 0 ((3129.71335 6726.99876) (3118.40769 6737.10667) (3110.85973 6738.31097)))
("SF_PLANTING" 0 ((3129.71335 6708.14480) (3103.32489 6708.29966) (3096.83303 6712.07014) (3093.21063 6730.76267)
(3099.55407 6737.10667) (3110.85973 6738.31097)))
("SF_PLANTING" 0 ((3112.74502 507.16346) (3141.02557 496.53959) (3193.81606 460.93835) (3215.68620 454.75124)))
("SF_PLANTING" 0 ((3112.74502 507.16346) (3114.63054 460.03111)))
("SF_PLANTING" 0 ((3137.25498 422.32183) (3128.66346 444.94627) (3114.63054 460.03111)))
("SF_MASONRY_AND_ARCH" 0 ((3122.17195 2816.74208) (3118.40113 2794.11765)))
("SF_MASONRY_AND_ARCH" 0 ((3122.17195 2816.74208) (3167.42081 2824.13609) (3254.14774 2824.43156) (3269.23077
2828.04118) (3288.08439 2824.28382)))
("SF_PLANTING" 0 ((3122.17195 343.13631) (3126.99921 312.97229) (3137.25498 297.88744)))
("SF_PLANTING" 0 ((3148.56719 346.90894) (3122.17195 343.13631)))
("SF_MASONRY_AND_ARCH" 0 ((3306.93824 2006.03292) (3295.62568 2009.65645) (3190.04525 2009.81041) (3171.19163
2013.56844) (3125.94276 2009.80419)))
("SF_MASONRY_AND_ARCH" 0 ((3125.94276 1892.91075) (3129.41708 1885.07353) (3163.65000 1885.36980)))
("SF_PLANTING" 0 ((3129.71335 6726.99876) (3129.71335 6708.14480)))
("SF_PLANTING" 0 ((3129.71335 6726.99876) (3148.56719 6731.97353) (3167.42081 6745.85192)))
("SF_PLANTING" 0 ((3137.25498 6685.52036) (3136.05747 6700.59649) (3129.71335 6708.14480)))
("SF_MASONRY_AND_ARCH" 0 ((3129.71335 1843.89140) (3133.48416 1847.66188) (3133.48416 1858.97410)))
("SF_PLANTING" 0 ((3141.02557 6451.73462) (3133.48416 6444.19299)))
("SF_MASONRY_AND_ARCH" 0 ((3133.48416 2251.13122) (3159.87941 2262.28190) (3182.50385 2247.36075)))
("SF_MASONRY_AND_ARCH" 0 ((3133.48416 1858.97410) (3152.33778 1862.73224) (3167.42081 1858.97410)))
("SF_PLANTING" 0 ((3137.25498 6843.89140) (3156.10860 6843.89140)))
("SF_PLANTING" 0 ((3174.96222 6683.63473) (3148.56719 6681.89774) (3137.25498 6685.52036)))
("SF_PLANTING" 0 ((3137.25498 6610.10532) (3133.49072 6595.02262) (3137.40973 6583.86527) (3144.79638 6580.09434)
(3171.19163 6579.93993)))
("SF_PLANTING" 0 ((3137.25498 422.32183) (3152.33122 414.77466) (3174.96222 384.61538)))
("SF_PLANTING" 0 ((3156.10860 248.86878) (3142.22342 267.72342) (3137.25498 297.88744)))
("SF_PLANTING" 0 ((3148.56719 346.90894) (3148.41912 312.97229) (3143.74661 301.81335) (3137.25498 297.88744)))
("SF_PLANTING" 0 ((3144.79638 6527.14932) (3141.02557 6534.69106)))
("SF_PLANTING" 0 ((3141.02557 6485.67127) (3174.96222 6478.12964)))
("SF_PLANTING" 0 ((3144.79638 6527.14932) (3141.02557 6485.67127)))
("SF_MASONRY_AND_ARCH" 0 ((3141.02557 1674.20814) (3137.26154 1689.29016) (3141.02557 1704.37500)))
("SF_MASONRY_AND_ARCH" 0 ((3141.02557 1674.20814) (3216.44050 1674.06041) (3235.29412 1670.43835) (3284.31380
1674.05351) (3306.93824 1666.66572)))
("SF_PLANTING" 0 ((3144.79638 6527.14932) (3159.87941 6527.14932)))
("SF_PLANTING" 0 ((3144.79638 6353.69525) (3159.87941 6353.69525)))
("SF_MASONRY_AND_ARCH" 0 ((3435.14321 1251.88631) (3386.12376 1259.27885) (3329.56267 1259.57432) (3288.08439
1274.36233) (3269.23077 1271.03507) (3254.14774 1274.50385) (3144.79638 1274.51075)))
("SF_MASONRY_AND_ARCH" 0 ((3148.56719 1293.36256) (3144.79638 1274.51075)))
("SF_MASONRY_AND_ARCH" 0 ((3148.56719 2450.98066) (3148.56719 2398.19005)))
("SF_MASONRY_AND_ARCH" 0 ((3148.56719 987.93269) (3231.52330 987.92783) (3250.37715 984.17534) (3273.00158 987.92647)
(3291.85520 984.17534) (3318.25045 991.55690) (3438.91403 990.03371) (3495.47511 995.32738) (3574.66063 995.62285)
(3589.74367 999.24491)))
("SF_PLANTING" 0 ((3148.56719 346.90894) (3174.96222 384.61538)))
("SF_MASONRY_AND_ARCH" 0 ((3152.33778 1172.70079) (3216.44050 1172.70079)))
("SF_PLANTING" 0 ((3167.42081 6798.64253) (3160.93552 6809.95475) (3156.10860 6843.89140)))
("SF_PLANTING" 0 ((3156.10860 6843.89140) (3166.36448 6858.97410) (3172.24774 6885.36980) (3182.50385 6900.45249)))
("SF_PLANTING" 0 ((3156.10860 248.86878) (3190.04525 252.63857)))
("SF_PLANTING" 0 ((3159.87941 6527.14932) (3171.19163 6520.66403) (3186.27443 6519.75588) (3201.20283 6527.29762)
(3204.97364 6534.69106) (3201.20283 6557.16719) (3171.19163 6572.39819)))
("SF_PLANTING" 0 ((3159.87941 6527.14932) (3170.14186 6553.54423) (3171.19163 6572.39819)))
("SF_PLANTING" 0 ((3159.87941 6353.69525) (3171.19163 6342.38303)))
("SF_PLANTING" 0 ((3205.12828 6357.46606) (3208.74412 6368.77828) (3203.93043 6383.85475) (3197.58009 6390.19819)
(3190.04525 6391.24152) (3163.80464 6368.77828) (3159.87941 6353.69525)))
("SF_PLANTING" 0 ((3171.19163 6319.75860) (3160.92930 6297.13416) (3159.87941 6282.05136)))
("SF_PLANTING" 0 ((3167.42081 6768.47636) (3163.65000 6783.55984)))
("SF_PLANTING" 0 ((3167.42081 6798.64253) (3163.65000 6783.55984)))
("SF_PLANTING" 0 ((3167.42081 6798.64253) (3210.78439 6817.49649)))
("SF_PLANTING" 0 ((3167.42081 6768.47636) (3167.42081 6745.85192)))
("SF_PLANTING" 0 ((3167.42081 6768.47636) (3208.89887 6776.01810)))
("SF_PLANTING" 0 ((3171.19163 6734.53971) (3167.42081 6745.85192)))
("SF_PLANTING" 0 ((3167.42081 6426.59627) (3174.96222 6451.73462)))
("SF_PLANTING" 0 ((3171.19163 6734.53971) (3197.58665 6729.71324) (3212.66968 6722.17149) (3227.75271 6704.37432)))
("SF_PLANTING" 0 ((3171.19163 6734.53971) (3171.33982 6692.99446) (3174.96222 6683.63473)))
("SF_PLANTING" 0 ((3171.19163 6572.39819) (3171.19163 6579.93993)))
("SF_PLANTING" 0 ((3174.96222 6683.63473) (3173.90611 6659.12545) (3160.17568 6628.95928) (3171.19163 6579.93993)))
("SF_PLANTING" 0 ((3174.96222 6683.63473) (3190.04525 6689.14299) (3212.66968 6690.49514) (3227.75271 6704.37432)))
("SF_PLANTING" 0 ((3174.96222 6478.12964) (3174.96222 6451.73462)))
("SF_PLANTING" 0 ((3174.96222 6478.12964) (3197.58665 6484.47376) (3299.39661 6481.90045)))
("SF_PLANTING" 0 ((3186.27443 6447.96380) (3174.96222 6451.73462)))
("SF_PLANTING" 0 ((3174.96222 6229.26086) (3174.96222 6251.88529)))
("SF_PLANTING" 0 ((3201.35747 377.07296) (3174.96222 384.61538)))
("SF_PLANTING" 0 ((3178.73303 6930.61867) (3178.73303 6919.30645)))
("SF_PLANTING" 0 ((3178.73303 6930.61867) (3160.02760 6945.70136) (3149.76482 6960.78405) (3134.53394 7002.26244)
(3122.46810 7051.28179) (3126.99921 7062.59400) (3141.02557 7077.52919) (3163.65000 7088.83462) (3178.58495 7081.44140)
(3190.04525 7055.05305)))
("SF_PLANTING" 0 ((3178.73303 6930.61867) (3190.04525 6945.70136)))
("SF_PLANTING" 0 ((3182.50385 6900.45249) (3178.73303 6919.30645)))
("SF_MASONRY_AND_ARCH" 0 ((3178.73303 2130.46731) (3182.50385 2156.86278)))
("SF_PLANTING" 0 ((3197.58665 6896.68201) (3182.50385 6900.45249)))
("SF_MASONRY_AND_ARCH" 0 ((3182.50385 2156.86278) (3212.66968 2156.86278) (3291.85520 2156.86278)))
("SF_PLANTING" 0 ((3325.79186 7115.38462) (3291.85520 7110.55769) (3254.29581 7085.21844) (3228.80260 7047.51131)
(3217.49661 7021.11640) (3215.38416 7006.03292) (3191.10158 6960.78405) (3190.04525 6945.70136)))
("SF_PLANTING" 0 ((3254.14774 6983.40848) (3243.89152 6979.48314) (3220.20452 6946.90566) (3190.04525 6945.70136)))
("SF_PLANTING" 0 ((3190.04525 252.63857) (3190.04525 267.72342)))
("SF_PLANTING" 0 ((3201.35747 369.53337) (3171.33982 309.19966) (3172.39581 282.80543) (3190.04525 267.72342)))
("SF_PLANTING" 0 ((3208.89887 279.03563) (3190.04525 267.72342)))
("SF_PLANTING" 0 ((3190.04525 252.63857) (3205.12828 233.78586) (3223.98190 233.78586) (3254.14774 233.78586)))
("SF_PLANTING" 0 ((3216.44050 6851.43314) (3207.84242 6881.59853) (3197.58665 6896.68201)))
("SF_PLANTING" 0 ((3197.58665 6896.68201) (3216.44050 6904.20984) (3254.14774 6893.05905) (3306.93167 6893.05905)
(3314.47964 6896.68201)))
("SF_MASONRY_AND_ARCH" 0 ((3205.12828 3197.58699) (3197.58665 3193.81572)))
("SF_MASONRY_AND_ARCH" 0 ((3201.35747 1877.82805) (3205.28303 1870.42794) (3220.21109 1862.89378) (3333.33326
1862.73914) (3348.41629 1859.27036) (3401.20656 1866.36810) (3442.68450 1862.75226) (3453.99706 1866.51584)))
("SF_PLANTING" 0 ((3201.35747 377.07296) (3201.35747 369.53337)))
("SF_PLANTING" 0 ((3201.35747 377.07296) (3206.33247 399.69253) (3216.44050 407.23982)))
("SF_PLANTING" 0 ((3201.35747 369.53337) (3235.29412 369.53337)))
("SF_MASONRY_AND_ARCH" 0 ((3216.44050 3193.81572) (3205.12828 3197.58699)))
("SF_MASONRY_AND_ARCH" 0 ((3205.12828 3197.58699) (3205.27647 3223.97500) (3208.89887 3231.52364)))
("SF_PLANTING" 0 ((3208.89887 6776.01810) (3242.83552 6776.01810)))
("SF_PLANTING" 0 ((3208.89887 6776.01810) (3210.78439 6817.49649)))
("SF_PLANTING" 0 ((3208.89887 6632.72975) (3246.60633 6625.18880)))
("SF_MASONRY_AND_ARCH" 0 ((3231.52330 3412.51912) (3208.89887 3412.51912)))
("SF_PLANTING" 0 ((3208.89887 279.03563) (3231.52330 277.97851) (3250.22251 267.57500) (3253.99299 260.18100)
(3254.14774 233.78586)))
("SF_PLANTING" 0 ((3208.89887 279.03563) (3213.72602 305.42986) (3231.52330 324.13609) (3246.60633 331.82410)))
("SF_PLANTING" 0 ((3242.83552 6776.01810) (3242.68077 6802.41301) (3238.91029 6809.80645) (3227.75271 6816.43971)
(3210.78439 6817.49649)))
("SF_PLANTING" 0 ((3216.44050 6851.43314) (3210.78439 6817.49649)))
("SF_PLANTING" 0 ((3246.60633 452.48869) (3215.68620 454.75124)))
("SF_PLANTING" 0 ((3215.68620 454.75124) (3216.44050 407.23982)))
("SF_PLANTING" 0 ((3215.68620 454.75124) (3212.66968 460.03111) (3220.21109 463.80090)))
("SF_PLANTING" 0 ((3215.68620 454.75124) (3220.21109 463.80090)))
("SF_PLANTING" 0 ((3216.44050 6851.43314) (3242.83552 6855.05532) (3280.54299 6840.12093)))
("SF_MASONRY_AND_ARCH" 0 ((3227.75271 1131.22172) (3220.35916 1132.42658) (3216.59525 1138.76900) (3216.44050
1172.70079)))
("SF_MASONRY_AND_ARCH" 0 ((3431.37262 1191.55260) (3355.95769 1191.40554) (3340.87489 1187.79525) (3325.79186
1190.34921) (3303.16742 1176.62523) (3231.52330 1176.32285) (3216.44050 1172.70079)))
("SF_PLANTING" 0 ((3246.60633 388.38518) (3239.05837 398.50023) (3216.44050 407.23982)))
("SF_MASONRY_AND_ARCH" 0 ((3220.21109 2756.41052) (3220.21109 2733.78609)))
("SF_MASONRY_AND_ARCH" 0 ((3220.21109 2756.41052) (3235.29412 2760.03326) (3340.87455 2761.69785) (3352.18710
2752.63925)))
("SF_MASONRY_AND_ARCH" 0 ((3223.98190 2202.11188) (3306.93824 2199.53857) (3420.06041 2202.11165) (3438.91403
2202.11165) (3548.26538 2202.11165)))
("SF_PLANTING" 0 ((3239.06493 6704.37432) (3227.75271 6704.37432)))
("SF_MASONRY_AND_ARCH" 0 ((3227.75271 3325.79186) (3227.75271 3257.91855)))
("SF_MASONRY_AND_ARCH" 0 ((3235.29412 3374.81120) (3227.90090 3355.95803) (3227.75271 3325.79186)))
("SF_MASONRY_AND_ARCH" 0 ((3344.64548 3246.60633) (3306.93824 3254.00034) (3235.30068 3254.29581) (3227.75271
3257.91855)))
("SF_MASONRY_AND_ARCH" 0 ((3227.75271 2247.36075) (3235.29412 2251.13122)))
("SF_MASONRY_AND_ARCH" 0 ((3231.52330 3412.51912) (3265.45995 3412.51912)))
("SF_MASONRY_AND_ARCH" 0 ((3231.52330 3412.51912) (3231.67138 3382.35984) (3235.29412 3374.81120)))
("SF_ARCHITECTURE" 0 ((3235.29412 5829.56267) (3804.67613 5829.56267)))
("SF_ARCHITECTURE" 0 ((3235.29412 5829.56267) (3235.44876 5803.17398) (3242.84208 5795.62590) (3759.42692 5795.62590)
(3778.28054 5795.62590) (3793.36324 5795.62590) (3804.67613 5799.39661)))
("SF_MASONRY_AND_ARCH" 0 ((3288.08439 3378.58247) (3235.29412 3374.81120)))
("SF_PLANTING" 0 ((3235.29412 863.49830) (3235.29412 874.81052)))
("SF_PLANTING" 0 ((3318.25045 493.96776) (3339.81855 512.81957) (3354.90781 546.75622) (3352.03903 629.71437)
(3341.93100 652.33880) (3328.50667 708.89989) (3292.75034 795.62500) (3253.99955 855.80339) (3235.29412 863.49830)))
("SF_PLANTING" 0 ((3291.85520 565.61086) (3285.51143 569.53597) (3283.25747 588.23529) (3273.15633 607.08993)
(3265.31176 690.04525) (3251.42704 720.21210) (3235.14604 818.24943) (3227.90090 837.10407) (3228.80882 855.95113)
(3235.29412 863.49830)))
("SF_PLANTING" 0 ((3235.29412 369.53337) (3246.60633 331.82410)))
("SF_PLANTING" 0 ((3246.60633 388.38518) (3235.29412 369.53337)))
("SF_PLANTING" 0 ((3239.06493 6930.61867) (3284.31380 6934.38914)))
("SF_PLANTING" 0 ((3239.06493 6704.37432) (3249.17964 6685.52036) (3254.14774 6655.35419)))
("SF_PLANTING" 0 ((3257.91855 6742.08145) (3252.94355 6715.83405) (3239.06493 6704.37432)))
("SF_ARCHITECTURE" 0 ((3242.83552 5705.12828) (3239.06493 5712.66968)))
("SF_PLANTING" 0 ((3242.83552 6776.01810) (3254.14774 6768.47636)))
("SF_ARCHITECTURE" 0 ((3242.83552 3797.13382) (3242.83563 4091.25147) (3242.83563 4113.87590) (3242.83563 4328.80803)
(3242.83563 4343.89140) (3242.83563 4355.20362) (3242.83563 4430.61799) (3242.83563 4453.24242) (3242.83563 5659.87941)
(3242.83563 5690.04525) (3242.83552 5705.12828)))
("SF_ARCHITECTURE" 0 ((3242.83552 5705.12828) (3261.68937 5708.89887) (3288.08450 5705.12828)))
("SF_ARCHITECTURE" 0 ((3242.83552 3797.13382) (3261.68937 3793.36391) (3785.82161 3793.37014) (3800.90498 3797.13382)))
("SF_PLANTING" 0 ((3250.37715 6617.64706) (3246.60633 6625.18880)))
("SF_PLANTING" 0 ((3246.60633 6625.18880) (3253.09785 6640.27149) (3254.14774 6655.35419)))
("SF_PLANTING" 0 ((3246.60633 452.48869) (3265.45995 452.48869)))
("SF_PLANTING" 0 ((3246.60633 452.48869) (3261.68937 395.92760)))
("SF_PLANTING" 0 ((3246.60633 388.38518) (3254.14774 388.38518)))
("SF_PLANTING" 0 ((3310.70882 275.26301) (3291.86176 282.96007) (3269.08269 316.74208) (3254.15430 330.62070)
(3246.60633 331.82410)))
("SF_PLANTING" 0 ((3250.37715 6617.64706) (3269.23077 6612.82014) (3299.39661 6595.02262)))
("SF_PLANTING" 0 ((3265.45995 6576.16867) (3255.35181 6587.48122) (3250.37715 6617.64706)))
("SF_PLANTING" 0 ((3254.14774 6983.40848) (3255.20407 6998.49197) (3266.51595 7021.11640) (3303.16742 7070.13575)))
("SF_PLANTING" 0 ((3254.14774 6983.40848) (3276.77217 6984.46527) (3303.16742 7001.20645) (3329.56267 7002.41075)
(3355.95769 7013.57466)))
("SF_PLANTING" 0 ((3261.68937 6768.47636) (3254.14774 6768.47636)))
("SF_PLANTING" 0 ((3257.91855 6742.08145) (3250.53190 6749.62975) (3254.14774 6768.47636)))
("SF_PLANTING" 0 ((3314.47964 6617.64706) (3306.93167 6632.72319) (3276.77217 6654.15667) (3254.14774 6655.35419)))
("SF_MASONRY_AND_ARCH" 0 ((3254.14774 3190.04525) (3295.62602 3190.04525)))
("SF_MASONRY_AND_ARCH" 0 ((3261.68937 2620.66391) (3254.14774 2620.66391)))
("SF_PLANTING" 0 ((3288.08439 369.53337) (3269.23733 370.73676) (3254.14774 388.38518)))
("SF_PLANTING" 0 ((3261.68937 395.92760) (3254.14774 388.38518)))
("SF_PLANTING" 0 ((3314.47964 248.86878) (3291.85520 233.78586) (3254.14774 233.78586)))
("SF_PLANTING" 0 ((3257.91855 6742.08145) (3269.23077 6749.62319)))
("SF_MASONRY_AND_ARCH" 0 ((3261.68937 2620.66391) (3254.44389 2586.72726) (3257.91855 2575.41505)))
("SF_MASONRY_AND_ARCH" 0 ((3344.64548 2579.18552) (3257.91855 2575.41505)))
("SF_PLANTING" 0 ((3269.23077 6749.62319) (3261.68937 6768.47636)))
("SF_PLANTING" 0 ((3286.19910 6772.24762) (3261.68937 6768.47636)))
("SF_MASONRY_AND_ARCH" 0 ((3261.68937 2620.66391) (3273.00158 2624.28665) (3344.64548 2624.43439)))
("SF_PLANTING" 0 ((3288.08439 395.92760) (3261.68937 395.92760)))
("SF_PLANTING" 0 ((3265.45995 6576.16867) (3265.60803 6553.55113) (3269.23077 6546.00328)))
("SF_PLANTING" 0 ((3265.45995 6576.16867) (3299.39661 6587.48088)))
("SF_PLANTING" 0 ((3299.39661 414.78224) (3275.72262 448.56357) (3265.45995 452.48869)))
("SF_PLANTING" 0 ((3286.19910 6772.24762) (3283.10939 6753.54853) (3269.23077 6749.62319)))
("SF_MASONRY_AND_ARCH" 0 ((3276.77217 2100.30192) (3269.23077 2100.30192)))
("SF_PLANTING" 0 ((3286.19910 6772.24762) (3287.86233 6779.79548) (3280.54299 6806.18428)))
("SF_MASONRY_AND_ARCH" 0 ((3348.41629 3416.28959) (3340.86833 3412.66686) (3280.54299 3412.51912)))
("SF_MASONRY_AND_ARCH" 0 ((3280.54299 2892.15713) (3291.85520 2895.77986) (3344.64548 2895.92760)))
("SF_MASONRY_AND_ARCH" 0 ((3306.93824 1131.22172) (3280.54299 1131.22172)))
("SF_PLANTING" 0 ((3284.31380 6934.38914) (3314.47964 6896.68201)))
("SF_PLANTING" 0 ((3284.31380 6934.38914) (3303.16742 6938.15962)))
("SF_MASONRY_AND_ARCH" 0 ((3284.31380 2266.21391) (3355.95769 2269.83744) (3367.26991 2266.36165) (3408.74819
2266.06618) (3431.37262 2258.67296)))
("SF_PLANTING" 0 ((3286.19910 6772.24762) (3310.70882 6768.63122) (3329.56267 6783.55984)))
("SF_MASONRY_AND_ARCH" 0 ((3340.87489 2805.42986) (3303.16742 2807.68348) (3288.08439 2824.28382)))
("SF_MASONRY_AND_ARCH" 0 ((3291.85520 2843.13699) (3288.08439 2824.28382)))
("SF_MASONRY_AND_ARCH" 0 ((3687.78281 2100.30192) (3661.38756 2092.76018) (3582.20204 2092.91482) (3564.18416
2103.70373) (3544.49480 2098.63032) (3518.09955 2100.15419) (3506.78733 2096.82692) (3495.47511 2100.01256) (3427.60181
2100.29570) (3386.12376 2096.53688) (3363.49932 2100.30192) (3318.25045 2096.53688) (3288.08439 2100.30192)))
("SF_PLANTING" 0 ((3288.08439 395.92760) (3288.08439 369.53337)))
("SF_PLANTING" 0 ((3288.08439 395.92760) (3299.39661 414.78224)))
("SF_PLANTING" 0 ((3288.08439 369.53337) (3309.65894 316.74208) (3314.46652 286.57523) (3310.70882 275.26301)))
("SF_ARCHITECTURE" 0 ((3322.02115 5705.12828) (3288.08450 5705.12828)))
("SF_ARCHITECTURE" 0 ((3306.18394 5021.87014) (3295.89253 5022.89717) (3288.08450 5033.93665) (3288.08450 5403.46867)
(3288.08450 5426.09310) (3288.08450 5641.02557) (3288.08450 5656.10860) (3288.08450 5705.12828)))
("SF_PLANTING" 0 ((3291.85520 565.61086) (3292.00328 550.52885) (3304.36538 505.28484) (3318.25045 493.96776)))
("SF_PLANTING" 0 ((3291.85520 565.61086) (3303.16742 576.92308)))
("SF_MASONRY_AND_ARCH" 0 ((3299.39661 2051.28179) (3295.62602 2062.59400)))
("SF_PLANTING" 0 ((3299.39661 6587.48088) (3299.39661 6595.02262)))
("SF_PLANTING" 0 ((3314.47964 6617.64706) (3299.39661 6595.02262)))
("SF_PLANTING" 0 ((3299.39661 6587.48088) (3318.25045 6591.25215)))
("SF_PLANTING" 0 ((3714.17805 6478.12975) (3691.55362 6478.12975) (3665.15837 6478.12975) (3299.39661 6481.90045)))
("SF_PLANTING" 0 ((3306.93824 6534.69106) (3299.54468 6515.83710) (3299.39661 6481.90045)))
("SF_MASONRY_AND_ARCH" 0 ((3299.39661 1504.52489) (3306.79016 1530.91912) (3306.93824 1561.08597)))
("SF_MASONRY_AND_ARCH" 0 ((3570.88982 1496.98247) (3484.16290 1500.90215) (3438.91403 1508.28982) (3299.39661
1504.52489)))
("SF_PLANTING" 0 ((3299.39661 414.78224) (3318.25045 414.78224)))
("SF_PLANTING" 0 ((3333.33326 6904.22296) (3307.09299 6926.84740) (3303.16742 6938.15962)))
("SF_PLANTING" 0 ((3318.25045 6960.78405) (3303.16742 6938.15962)))
("SF_PLANTING" 0 ((3303.16742 6726.99876) (3311.90633 6696.83258) (3322.02104 6685.52036)))
("SF_ARCHITECTURE" 0 ((3303.16742 4826.54559) (3303.16742 4506.03360)))
("SF_ARCHITECTURE" 0 ((3306.93824 4966.06335) (3296.68213 4958.51538) (3288.08450 4943.43891) (3288.08450 4841.62896)
(3303.16742 4826.54559)))
("SF_ARCHITECTURE" 0 ((3306.93824 4966.06335) (3322.02115 4950.97998) (3322.02115 4841.62896) (3303.16742 4826.54559)))
("SF_ARCHITECTURE" 0 ((3303.16742 4506.03360) (3322.02115 4494.72070) (3322.02115 4483.40916) (3322.02115 4468.32579)
(3303.16742 4453.24242)))
("SF_ARCHITECTURE" 0 ((3303.16742 4506.03360) (3292.91154 4498.48507) (3284.31369 4479.63801) (3284.31369 4468.32579)
(3303.16742 4453.24242)))
("SF_ARCHITECTURE" 0 ((3303.16742 4453.24242) (3303.17398 3880.09050) (3306.92511 3861.23722) (3303.16742 3849.92500)))
("SF_MASONRY_AND_ARCH" 0 ((3306.93824 1598.79242) (3303.16742 1606.33484)))
("SF_MASONRY_AND_ARCH" 0 ((3303.16742 1606.33484) (3314.47964 1625.18948)))
("SF_ARCHITECTURE" 0 ((3306.18394 5021.87014) (3306.93824 4966.06335)))
("SF_ARCHITECTURE" 1 ((3306.18394 5021.87014) (3306.93824 5030.16550) (3303.16742 5026.39559)))
("SF_ARCHITECTURE" 0 ((3306.18394 5021.87014) (3322.02115 5033.93529) (3322.02115 5105.58111) (3322.02115 5120.66324)
(3322.02115 5316.74208) (3322.02115 5339.36652) (3322.02115 5392.15645) (3322.02115 5411.01097) (3322.02115 5659.87941)
(3322.02115 5686.27443) (3322.02115 5705.12828)))
("SF_MASONRY_AND_ARCH" 0 ((3314.47964 1625.18948) (3303.31550 1647.81391) (3306.93824 1666.66572)))
("SF_MASONRY_AND_ARCH" 0 ((3306.93824 1666.66572) (3325.79186 1670.43835)))
("SF_MASONRY_AND_ARCH" 0 ((3306.93824 1131.22172) (3310.70882 1116.13971)))
("SF_MASONRY_AND_ARCH" 0 ((3310.70882 1153.84615) (3306.93824 1131.22172)))
("SF_MASONRY_AND_ARCH" 0 ((3306.93824 889.89536) (3314.47964 882.35294)))
("SF_PLANTING" 0 ((3314.47964 637.25396) (3306.93824 622.17195)))
("SF_MASONRY_AND_ARCH" 0 ((3310.70882 3107.08925) (3348.41629 3114.63020)))
("SF_PLANTING" 0 ((3310.70882 275.26301) (3314.47964 248.86878)))
("SF_PLANTING" 0 ((3333.33326 6896.68201) (3314.47964 6896.68201)))
("SF_PLANTING" 0 ((3314.47964 6617.64706) (3322.02104 6617.64706)))
("SF_MASONRY_AND_ARCH" 0 ((3582.20204 1606.33484) (3577.23360 1621.26357) (3570.88326 1625.03416) (3314.47964
1625.18948)))
("SF_PLANTING" 0 ((3374.81154 248.86878) (3348.41629 241.32636) (3314.47964 248.86878)))
("SF_MASONRY_AND_ARCH" 0 ((3318.25045 1297.13518) (3322.02104 1331.07183)))
("SF_PLANTING" 0 ((3318.25045 493.96776) (3314.48620 471.34333) (3318.25045 414.78224)))
("SF_PLANTING" 0 ((3344.64548 361.99095) (3338.29514 365.91606) (3324.60079 407.23292) (3318.25045 414.78224)))
("SF_PLANTING" 0 ((3322.02104 6825.03744) (3359.72851 6833.77692) (3374.81154 6847.66188)))
("SF_MASONRY_AND_ARCH" 0 ((3337.10407 3378.58247) (3322.02104 3378.58247)))
("SF_MASONRY_AND_ARCH" 0 ((3593.51425 1334.84163) (3491.70430 1334.84785) (3472.85068 1338.59898) (3453.99706
1334.84785) (3329.56923 1334.69389) (3322.02104 1331.07183)))
("SF_MASONRY_AND_ARCH" 0 ((3322.02104 1217.94966) (3337.10407 1217.94966)))
("SF_ARCHITECTURE" 0 ((3322.02115 5705.12828) (3355.95769 5708.74412) (3363.49921 5701.35747)))
("SF_PLANTING" 0 ((3344.64548 7096.53066) (3325.79186 7115.38462)))
("SF_PLANTING" 0 ((3344.64548 7096.53066) (3352.03247 7104.07896) (3348.26165 7121.86301) (3337.10407 7123.67308)
(3325.79186 7115.38462)))
("SF_PLANTING" 0 ((3329.56267 6783.55984) (3325.79186 6791.10079)))
("SF_PLANTING" 0 ((3329.56267 6783.55984) (3389.89434 6787.32376) (3416.28959 6780.08484) (3431.37262 6783.55328)
(3597.28507 6783.55984) (3619.90950 6779.79514) (3706.63643 6779.78857)))
("SF_MASONRY_AND_ARCH" 0 ((3352.18710 2662.14152) (3344.63891 2655.79842) (3329.56267 2654.60057)))
("SF_MASONRY_AND_ARCH" 0 ((3359.72851 1444.19400) (3352.18054 1440.56980) (3329.56267 1440.42138)))
("SF_PLANTING" 0 ((3333.33326 6896.68201) (3333.33326 6904.22296)))
("SF_PLANTING" 0 ((3367.26991 6919.30645) (3348.41629 6914.33767) (3333.33326 6904.22296)))
("SF_PLANTING" 0 ((3333.33326 6896.68201) (3348.56437 6874.05758) (3374.81154 6847.66188)))
("SF_MASONRY_AND_ARCH" 0 ((3333.33326 1817.49717) (3446.45543 1817.49027) (3465.30928 1813.73835) (3484.16290
1817.49027) (3514.32873 1814.02149) (3567.11923 1817.49717)))
("SF_MASONRY_AND_ARCH" 0 ((3337.10407 2009.80419) (3401.20000 2009.95192) (3408.74819 2013.57466)))
("SF_PLANTING" 0 ((3344.64548 7096.53066) (3340.87489 7081.44796)))
("SF_PLANTING" 0 ((3344.64548 7043.74084) (3350.99615 7036.19253) (3355.95769 7013.57466)))
("SF_PLANTING" 0 ((3374.81154 275.26301) (3357.01403 290.49491) (3349.47262 305.42986) (3344.64548 361.99095)))
("SF_PLANTING" 0 ((3363.49932 384.61538) (3344.64548 361.99095)))
("SF_MASONRY_AND_ARCH" 0 ((3348.41629 3178.73303) (3344.64548 3190.04525) (3348.41629 3193.81572)))
("SF_MASONRY_AND_ARCH" 0 ((3352.18710 2843.13699) (3348.41629 2854.44921)))
("SF_MASONRY_AND_ARCH" 0 ((3348.41629 1738.31165) (3363.49932 1738.31165)))
("SF_MASONRY_AND_ARCH" 0 ((3348.41629 1670.43835) (3378.58213 1670.43835)))
("SF_PLANTING" 0 ((3465.30928 825.79186) (3446.45543 822.02692) (3348.41629 822.02206)))
("SF_MASONRY_AND_ARCH" 0 ((3352.18710 3152.33812) (3352.18710 3159.87907)))
("SF_PLANTING" 0 ((3397.43597 6975.86753) (3355.95769 7013.57466)))
("SF_PLANTING" 0 ((3367.26991 6919.30645) (3367.11516 6934.38914) (3359.72851 6949.47183)))
("SF_ARCHITECTURE" 0 ((3397.43586 5701.35747) (3363.49921 5701.35747)))
("SF_ARCHITECTURE" 0 ((3378.58213 5595.77636) (3363.49921 5610.85973) (3363.49921 5674.96222) (3363.49921 5701.35747)))
("SF_PLANTING" 0 ((3378.58213 6919.30645) (3367.26991 6919.30645)))
("SF_MASONRY_AND_ARCH" 0 ((3371.04072 1444.19400) (3416.28959 1440.42828) (3491.70430 1447.81606) (3514.32873
1444.48948) (3525.64095 1447.81606) (3574.66063 1448.11154) (3585.97285 1451.73360)))
("SF_PLANTING" 0 ((3420.06041 6851.43314) (3408.74785 6847.81018) (3374.81154 6847.66188)))
("SF_PLANTING" 0 ((3374.81154 275.26301) (3374.81154 248.86878)))
("SF_PLANTING" 0 ((3374.81154 275.26301) (3388.69016 286.57523) (3393.51708 305.42986) (3397.42941 343.13631)
(3394.86278 414.78224) (3401.20656 444.94627)))
("SF_PLANTING" 0 ((3374.81154 248.86878) (3397.43597 233.78586) (3423.83100 233.78586) (3442.68484 245.09898)))
("SF_PLANTING" 0 ((3378.58213 6919.30645) (3392.60882 6904.22296) (3402.26290 6881.59853) (3420.06041 6862.74536)))
("SF_PLANTING" 0 ((3378.58213 6919.30645) (3404.97738 6930.47036) (3435.13665 6930.47036) (3442.68484 6926.84740)))
("SF_ARCHITECTURE" 0 ((3378.58213 5595.77636) (3378.58213 3849.92500)))
("SF_ARCHITECTURE" 0 ((3397.43586 5701.35747) (3397.43586 5693.80950) (3397.43586 5614.63088) (3378.58213 5595.77636)))
("SF_PLANTING" 0 ((3465.30928 6953.24310) (3442.83303 6968.47410) (3431.22455 6987.17975) (3390.04932 7024.88688)
(3386.42658 7032.42172) (3389.89434 7039.96957)))
("SF_MASONRY_AND_ARCH" 0 ((3393.66516 1670.43835) (3404.97081 1671.63552) (3412.51878 1677.97794)))
("SF_ARCHITECTURE" 0 ((3397.43586 5701.35747) (3404.97738 5708.74412) (3427.60181 5708.75068) (3450.22624 5693.81606)))
("SF_PLANTING" 0 ((3435.14321 516.59219) (3457.76765 525.18891) (3479.18790 546.75622) (3501.96041 603.31731)
(3553.09219 773.00057) (3566.06290 799.39762) (3566.96459 814.47274) (3563.19378 820.80962) (3555.80667 820.95803)
(3529.41176 806.79016) (3480.54016 754.14876) (3458.81742 723.98190) (3421.10995 644.79638) (3393.81324 573.15328)
(3390.04242 471.34333) (3394.86278 452.49559) (3401.20656 444.94627)))
("SF_PLANTING" 0 ((3435.14321 516.59219) (3422.63337 460.03111) (3401.20656 444.94627)))
("SF_PLANTING" 0 ((3404.97738 7055.05305) (3412.52534 7058.66867) (3423.83100 7055.05305)))
("SF_MASONRY_AND_ARCH" 0 ((3416.28959 3061.84038) (3416.28959 2598.03948)))
("SF_MASONRY_AND_ARCH" 0 ((3416.28959 3061.84038) (3406.18156 3073.15260) (3401.35464 3092.00577) (3401.35464
3148.56686) (3404.82274 3159.87907) (3401.21312 3178.73303) (3404.97081 3220.21143) (3402.26290 3371.04072) (3408.89638
3381.29661) (3420.06041 3385.97500) (3499.24593 3386.12342)))
("SF_MASONRY_AND_ARCH" 0 ((3416.28959 3061.84038) (3431.21799 3080.69355) (3432.42907 3340.87455) (3439.06210
3352.03213) (3469.07986 3359.72229) (3495.47511 3355.95803)))
("SF_MASONRY_AND_ARCH" 0 ((3416.28959 2598.03948) (3442.69140 2572.84796) (3499.24581 2571.64378)))
("SF_MASONRY_AND_ARCH" 0 ((3499.24593 2545.24887) (3491.69774 2541.62613) (3442.68484 2541.48462) (3408.90294
2546.45305) (3405.13201 2552.79683) (3405.13201 2586.72726) (3416.28959 2598.03948)))
("SF_MASONRY_AND_ARCH" 0 ((3555.80701 1738.31165) (3495.47511 1734.53903) (3435.14321 1738.16324) (3417.49412
1730.61459) (3416.28959 1711.91459)))
("SF_PLANTING" 0 ((3420.06041 6862.74536) (3420.06041 6851.43314)))
("SF_PLANTING" 0 ((3420.06041 6862.74536) (3435.14321 6866.51584)))
("SF_PLANTING" 0 ((3529.41176 6836.34966) (3495.47511 6828.95656) (3469.07986 6828.95656) (3439.06210 6833.78348)
(3420.06041 6851.43314)))
("SF_MASONRY_AND_ARCH" 0 ((3423.83100 889.89536) (3442.68484 893.66516)))
("SF_PLANTING" 0 ((3435.14321 516.59219) (3428.79943 524.13937) (3427.60181 535.44400)))
("SF_MASONRY_AND_ARCH" 0 ((3431.37262 2239.81900) (3431.37262 2258.67296)))
("SF_MASONRY_AND_ARCH" 0 ((3616.13869 2243.58948) (3604.82647 2244.79367) (3585.97285 2258.51833) (3544.49480
2262.29570) (3446.45543 2262.43722) (3431.37262 2258.67296)))
("SF_MASONRY_AND_ARCH" 0 ((3657.61697 1199.09502) (3650.37805 1187.48665) (3450.22624 1187.78903) (3431.37262
1191.55260)))
("SF_MASONRY_AND_ARCH" 0 ((3435.14321 1251.88631) (3431.37262 1191.55260)))
("SF_PLANTING" 0 ((3431.37262 339.36652) (3436.33450 361.99095) (3450.23281 379.64072) (3469.07986 383.41742)
(3484.16290 377.07296)))
("SF_PLANTING" 0 ((3457.76765 6862.74536) (3435.14321 6866.51584)))
("SF_PLANTING" 0 ((3442.68484 6926.84740) (3435.14321 6866.51584)))
("SF_MASONRY_AND_ARCH" 0 ((3435.14321 1251.88631) (3465.30928 1255.64989) (3574.66063 1251.88631) (3616.13869
1255.65611)))
("SF_MASONRY_AND_ARCH" 0 ((3435.14321 942.68382) (3435.14321 923.83201)))
("SF_MASONRY_AND_ARCH" 0 ((3435.14321 923.83201) (3441.62851 908.74717) (3442.68484 893.66516)))
("SF_PLANTING" 0 ((3442.68484 6926.84740) (3465.30928 6930.61867)))
("SF_MASONRY_AND_ARCH" 0 ((3450.22624 889.89536) (3442.68484 893.66516)))
("SF_PLANTING" 0 ((3442.68484 263.95079) (3442.68484 245.09898)))
("SF_PLANTING" 0 ((3442.68484 263.95079) (3447.51176 290.34785) (3467.88880 324.28450) (3484.16290 377.07296)))
("SF_PLANTING" 0 ((3442.68484 263.95079) (3472.70260 272.69118) (3518.09955 324.13609) (3540.72398 342.08066)
(3559.57760 350.67873)))
("SF_PLANTING" 0 ((3574.66063 241.32636) (3559.57760 233.78586) (3465.30928 233.78586) (3442.68484 245.09898)))
("SF_ARCHITECTURE" 0 ((3453.99706 3846.15385) (3450.23281 3857.46606) (3450.22624 5693.81606)))
("SF_ARCHITECTURE" 0 ((3506.78733 5705.12828) (3491.70430 5710.56380) (3476.62149 5708.75068) (3450.22624 5693.81606)))
("SF_MASONRY_AND_ARCH" 0 ((3453.99706 1866.51584) (3447.65328 1889.13337) (3450.22624 1896.68201)))
("SF_MASONRY_AND_ARCH" 0 ((3608.59729 1855.20362) (3563.34842 1862.73914) (3518.09955 1858.98722) (3491.70430
1862.59762) (3480.39208 1859.27036) (3453.99706 1866.51584)))
("SF_PLANTING" 0 ((3472.85068 467.57070) (3461.54502 475.11934) (3453.99706 486.42534)))
("SF_PLANTING" 0 ((3465.30928 6953.24310) (3465.30928 6930.61867)))
("SF_PLANTING" 0 ((3465.30928 6953.24310) (3484.16290 6960.78405)))
("SF_PLANTING" 0 ((3527.52647 6896.68201) (3487.93371 6909.19174) (3465.30928 6930.61867)))
("SF_MASONRY_AND_ARCH" 0 ((3476.62149 3435.14355) (3465.46403 3446.45577) (3465.30928 3476.62115)))
("SF_MASONRY_AND_ARCH" 0 ((3702.86584 3476.62115) (3665.15837 3480.39242) (3601.05588 3476.62738) (3585.97285
3480.24468) (3503.01652 3480.54016) (3487.93371 3484.14977) (3465.30928 3476.62115)))
("SF_MASONRY_AND_ARCH" 0 ((3472.85068 1402.71493) (3487.93371 1399.24061) (3548.26538 1406.47229) (3563.34842
1402.86267) (3601.05588 1406.47986) (3619.90950 1402.72738) (3638.76312 1406.47229) (3733.03167 1406.64005) (3746.91686
1417.79695) (3751.88529 1432.88179)))
("SF_PLANTING" 0 ((3495.47511 6981.52364) (3488.83507 6981.36719) (3481.60271 6987.18937) (3476.62149 7024.88688)))
("SF_PLANTING" 0 ((3484.16290 6960.78405) (3487.93371 6957.01357) (3491.70430 6964.55532)))
("SF_PLANTING" 0 ((3484.16290 6960.78405) (3491.70430 6964.55532)))
("SF_MASONRY_AND_ARCH" 0 ((3499.24593 2488.68778) (3495.47511 2492.45826) (3484.16290 2492.45826)))
("SF_PLANTING" 0 ((3491.70430 384.61538) (3484.16290 377.07296)))
("SF_PLANTING" 0 ((3495.47511 6981.52364) (3491.70430 6964.55532)))
("SF_PLANTING" 0 ((3491.70430 384.61538) (3484.31753 399.69740) (3488.98982 422.32183) (3500.29548 444.94627)
(3540.87206 505.27998) (3589.74367 557.92138) (3619.90950 575.87364) (3668.92919 594.72059) (3714.17149 602.12014)
(3721.71946 599.54751)))
("SF_PLANTING" 0 ((3491.70430 384.61538) (3529.41176 404.51878) (3559.57760 433.63405)))
("SF_PLANTING" 0 ((3495.47511 6981.52364) (3513.27229 6960.78405) (3526.68416 6934.54400) (3533.18258 6930.61867)))
("SF_PLANTING" 1 ((3495.47511 6981.52364) (3491.70430 6987.17975) (3495.47511 6990.95023) (3499.24593 6987.17975)))
("SF_PLANTING" 0 ((3495.47511 6981.52364) (3506.64581 6983.63744) (3533.18258 7009.80419)))
("SF_MASONRY_AND_ARCH" 0 ((3495.47511 3355.95803) (3499.24581 3329.56233) (3499.24581 3280.54299) (3499.24581
3012.82025) (3499.24581 2990.19581) (3499.24581 2907.23982)))
("SF_MASONRY_AND_ARCH" 0 ((3495.47511 3355.95803) (3499.24593 3386.12342)))
("SF_MASONRY_AND_ARCH" 0 ((3499.24581 2907.23982) (3536.95328 2907.23982)))
("SF_MASONRY_AND_ARCH" 0 ((3499.24581 2571.64378) (3499.24581 2590.49774) (3499.24581 2639.51708) (3499.24581
2892.15713) (3499.24581 2907.23982)))
("SF_MASONRY_AND_ARCH" 0 ((3499.24593 2545.24887) (3499.24581 2571.64378)))
("SF_MASONRY_AND_ARCH" 0 ((3499.24593 3386.12342) (3521.87002 3385.06708) (3533.02794 3374.80498) (3536.95328
3122.17195) (3536.95328 3099.54751) (3536.95328 2907.23982)))
("SF_MASONRY_AND_ARCH" 0 ((3499.24593 2545.24887) (3529.40520 2546.45305) (3536.79842 2556.56109) (3536.95328
2620.66391) (3536.95328 2631.97613) (3536.95328 2647.05882) (3536.95328 2895.92760) (3536.95328 2907.23982)))
("SF_MASONRY_AND_ARCH" 0 ((3499.24593 2488.68778) (3499.24593 2473.60509)))
("SF_MASONRY_AND_ARCH" 0 ((3499.24593 2488.68778) (3540.72398 2492.45826)))
("SF_MASONRY_AND_ARCH" 0 ((3529.41176 897.43495) (3499.24593 897.43495)))
("SF_MASONRY_AND_ARCH" 0 ((3503.01652 2009.80419) (3567.11889 2009.95882) (3578.43145 2017.34514)))
("SF_ARCHITECTURE" 0 ((3503.01663 3834.84163) (3518.09955 3849.92500)))
("SF_PLANTING" 0 ((3506.78733 7066.36527) (3503.01652 7062.59400) (3514.32873 7051.28179)))
("SF_ARCHITECTURE" 0 ((3533.18258 5705.12828) (3506.78733 5705.12828)))
("SF_ARCHITECTURE" 0 ((3518.09955 5580.69423) (3506.94197 5592.00645) (3506.78733 5705.12828)))
("SF_MASONRY_AND_ARCH" 0 ((3589.74367 999.24491) (3588.53925 1021.86934) (3570.88982 1038.47036) (3521.87036 1040.71776)
(3506.78733 1036.95419)))
("SF_MASONRY_AND_ARCH" 0 ((3608.59729 2326.54627) (3533.18258 2325.34208) (3519.29751 2311.46278) (3514.32873
2296.38009)))
("SF_ARCHITECTURE" 0 ((3518.09955 5580.69423) (3518.09299 4287.33032) (3514.32873 4264.70588) (3518.09955 3849.92500)))
("SF_ARCHITECTURE" 0 ((3518.09955 5580.69423) (3533.18247 5588.24152) (3533.18247 5595.77636) (3533.18258 5705.12828)))
("SF_ARCHITECTURE" 0 ((3533.18247 3834.84163) (3518.09955 3849.92500)))
("SF_MASONRY_AND_ARCH" 0 ((3608.59729 2326.54627) (3612.21346 2368.02387) (3604.81991 2378.13201) (3518.09955
2379.33609)))
("SF_MASONRY_AND_ARCH" 0 ((3518.09955 2349.17070) (3518.09955 2379.33609)))
("SF_PLANTING" 0 ((3574.66063 260.18100) (3548.26538 271.34480) (3525.64095 267.72342)))
("SF_PLANTING" 0 ((3527.52647 6896.68201) (3529.41176 6836.34966)))
("SF_PLANTING" 0 ((3527.52647 6896.68201) (3533.18258 6930.61867)))
("SF_PLANTING" 0 ((3527.52647 6896.68201) (3574.66063 6901.96923) (3612.36810 6874.05758)))
("SF_PLANTING" 0 ((3529.41176 6836.34966) (3567.11923 6836.49796) (3612.36810 6851.43314)))
("SF_MASONRY_AND_ARCH" 0 ((3585.97285 878.58314) (3540.72398 883.55781) (3529.41176 897.43495)))
("SF_MASONRY_AND_ARCH" 0 ((3672.69977 916.28959) (3665.15181 908.90249) (3563.34842 904.82964) (3529.41176 897.43495)))
("SF_PLANTING" 0 ((3578.43145 6953.24310) (3533.18258 6930.61867)))
("SF_PLANTING" 0 ((3616.13869 6730.76923) (3567.11923 6730.76923) (3559.57760 6730.76923) (3548.26538 6730.76923)
(3540.72398 6730.76923) (3533.18258 6730.76923)))
("SF_ARCHITECTURE" 0 ((3533.18258 5705.12828) (3563.34842 5708.74412) (3585.97285 5693.81606)))
("SF_PLANTING" 0 ((3589.74367 482.65554) (3568.17568 460.03111) (3559.57760 433.63405)))
("SF_PLANTING" 0 ((3559.57760 433.63405) (3623.68032 458.98020) (3661.38756 467.42364) (3695.32421 467.71912)
(3736.80249 478.88292)))
("SF_PLANTING" 0 ((3578.43145 328.05430) (3571.03133 331.97941) (3559.57760 350.67873)))
("SF_PLANTING" 0 ((3593.51425 331.82410) (3588.54581 350.67183) (3582.19548 357.01629) (3567.12579 357.02251)
(3559.57760 350.67873)))
("SF_MASONRY_AND_ARCH" 0 ((4095.02262 2198.34061) (4046.00260 2202.10566) (4008.29604 2198.34683) (3895.17387
2198.34683) (3880.09050 2201.95724) (3865.00713 2198.48835) (3800.90498 2198.34683) (3785.82161 2201.96414) (3676.47059
2198.34061) (3653.84615 2202.11165) (3563.34842 2202.11165)))
("SF_PLANTING" 0 ((3604.82647 6994.72070) (3589.74367 6995.77093) (3575.85860 7002.41731) (3559.73880 7043.74084)
(3567.11923 7070.13575)))
("SF_MASONRY_AND_ARCH" 0 ((3570.88982 1496.98247) (3581.00441 1481.90045) (3585.97285 1451.73360)))
("SF_MASONRY_AND_ARCH" 0 ((3570.88982 1496.98247) (3578.43145 1515.83710)))
("SF_MASONRY_AND_ARCH" 0 ((3597.28507 1742.08145) (3574.66063 1738.31165)))
("SF_PLANTING" 0 ((3574.66063 241.32636) (3574.66063 260.18100)))
("SF_PLANTING" 0 ((3597.28507 290.34785) (3574.66063 260.18100)))
("SF_PLANTING" 0 ((3574.66063 241.32636) (3623.68032 237.70498) (3638.76312 245.09898)))
("SF_PLANTING" 0 ((3597.28507 6949.47183) (3578.43145 6953.24310)))
("SF_PLANTING" 0 ((3582.20204 6972.09627) (3578.43145 6953.24310)))
("SF_MASONRY_AND_ARCH" 0 ((3800.90498 1821.26697) (3796.97986 1814.77477) (3782.05136 1809.96097) (3619.90950
1809.96097) (3578.43145 1817.49717)))
("SF_PLANTING" 0 ((3578.43145 328.05430) (3579.63563 309.19966) (3597.28507 290.34785)))
("SF_PLANTING" 0 ((3593.51425 331.82410) (3582.20204 331.82410) (3578.43145 328.05430)))
("SF_MASONRY_AND_ARCH" 0 ((3585.97285 1557.31618) (3578.58620 1568.62839) (3582.20204 1606.33484)))
("SF_MASONRY_AND_ARCH" 0 ((3582.20204 1606.33484) (3604.82647 1606.48326) (3634.99253 1617.49932) (3748.11471
1613.87726)))
("SF_ARCHITECTURE" 0 ((3601.05577 3834.84163) (3586.12749 3846.15385) (3582.20860 3857.46606) (3582.35011 3898.94378)
(3585.96629 3914.02715) (3585.82477 3978.12930) (3582.20860 3993.21267) (3582.20860 4196.83258) (3585.97285 4219.45701)
(3585.82477 4264.70588) (3582.20860 4279.78925) (3582.20860 4792.60894) (3585.82477 4807.69231) (3585.97285 4856.71233)
(3582.20860 4879.33676) (3582.20204 5343.13767) (3585.96629 5365.76210) (3585.97285 5693.81606)))
("SF_ARCHITECTURE" 0 ((3659.50226 5691.93054) (3638.76312 5707.70124) (3608.59729 5707.84242) (3585.97285 5693.81606)))
("SF_MASONRY_AND_ARCH" 0 ((3872.54943 2511.31222) (3714.17805 2511.30600) (3672.69977 2507.54796) (3634.99253
2513.88484) (3601.05588 2503.77738) (3589.89842 2504.96844) (3585.97285 2511.31222)))
("SF_MASONRY_AND_ARCH" 0 ((3585.97285 2051.28179) (3601.05588 2055.05305) (3642.53394 2051.28179) (3699.09502
2054.89842) (3721.71946 2051.28179)))
("SF_MASONRY_AND_ARCH" 0 ((3585.97285 1451.73360) (3736.80215 1451.58032) (3744.19581 1447.80916) (3751.88529
1432.88179)))
("SF_MASONRY_AND_ARCH" 0 ((3604.82647 3412.51912) (3592.16855 3405.27353) (3589.74367 3382.35294)))
("SF_MASONRY_AND_ARCH" 0 ((3815.98835 3254.14808) (3774.50973 3261.53439) (3744.34389 3254.29581) (3702.86584
3254.00034) (3691.55362 3250.52455) (3616.13869 3250.38303) (3589.74367 3254.14808)))
("SF_MASONRY_AND_ARCH" 0 ((3589.74367 3050.52817) (3604.82647 3054.29864) (3623.68032 3050.52817)))
("SF_MASONRY_AND_ARCH" 0 ((3589.74367 2820.51256) (3611.16369 2816.58744) (3617.33620 2782.81233) (3627.45090
2775.26369)))
("SF_MASONRY_AND_ARCH" 0 ((3657.61697 2635.74661) (3657.46233 2609.35792) (3653.69152 2603.01414) (3589.74367
2598.03948)))
("SF_MASONRY_AND_ARCH" 0 ((3589.74367 999.24491) (3665.15837 991.71018) (3714.17805 991.85238) (3729.26086 995.47511)))
("SF_PLANTING" 0 ((3601.05588 509.04977) (3590.94785 497.73756) (3589.74367 482.65554)))
("SF_PLANTING" 0 ((3589.74367 482.65554) (3608.59729 483.85271) (3650.07534 516.73925) (3676.47715 550.52127)
(3710.25916 576.92930) (3721.71946 599.54751)))
("SF_PLANTING" 0 ((3604.82647 7141.77952) (3589.89842 7130.46075) (3586.12749 7122.92636) (3588.21369 7096.68552)
(3593.51425 7092.76018)))
("SF_MASONRY_AND_ARCH" 0 ((3593.51425 3182.50351) (3601.06244 3186.12014) (3616.13869 3182.50351)))
("SF_MASONRY_AND_ARCH" 0 ((3593.51425 3122.17195) (3607.40588 3141.02590) (3616.13869 3182.50351)))
("SF_MASONRY_AND_ARCH" 0 ((3616.13869 2997.73756) (3593.51425 2993.96708)))
("SF_MASONRY_AND_ARCH" 0 ((3593.51425 2631.97613) (3601.06244 2635.59887) (3657.61697 2635.74661)))
("SF_MASONRY_AND_ARCH" 0 ((3657.61697 2533.93665) (3656.41256 2549.01312) (3650.06878 2555.35690) (3593.51425
2552.79061)))
("SF_MASONRY_AND_ARCH" 0 ((3597.28507 1742.08145) (3593.51425 1764.70588)))
("SF_PLANTING" 0 ((3593.51425 331.82410) (3604.67828 327.89966) (3611.31176 316.74208) (3612.36810 290.34785)))
("SF_PLANTING" 0 ((3597.28507 6949.47183) (3598.48959 6930.61867) (3616.13869 6915.53518)))
("SF_PLANTING" 0 ((3597.28507 6949.47183) (3615.98394 6960.79095) (3619.90950 6975.86753)))
("SF_MASONRY_AND_ARCH" 0 ((3981.90045 2892.15713) (3970.58824 2895.77986) (3849.92500 2895.92760) (3831.07048
2895.92760) (3812.21719 2895.92760) (3623.68032 2895.92760) (3597.28507 2895.92760)))
("SF_MASONRY_AND_ARCH" 0 ((3597.28507 1742.08145) (3619.90950 1738.31165)))
("SF_PLANTING" 0 ((3612.36810 290.34785) (3597.28507 290.34785)))
("SF_MASONRY_AND_ARCH" 0 ((3970.58824 1945.70136) (3955.50486 1948.27398) (3891.40271 1941.94400) (3872.54943
1945.69514) (3831.07048 1942.08552) (3778.28054 1945.55362) (3766.96833 1942.07862) (3721.86753 1941.56210) (3706.63643
1927.00204) (3616.13869 1926.84118) (3601.05588 1923.07692)))
("SF_PLANTING" 0 ((3601.05588 727.75170) (3623.68032 731.52432) (3793.36391 731.51742) (3819.75826 725.17986)
(3857.46606 731.51742) (3978.12930 731.37590) (3996.98382 725.17986) (4110.10600 727.75170)))
("SF_PLANTING" 0 ((3604.82647 6994.72070) (3619.90950 6975.86753)))
("SF_PLANTING" 0 ((3604.82647 6994.72070) (3608.44265 7024.88688) (3604.97455 7047.50475) (3608.59729 7055.05305)))
("SF_MASONRY_AND_ARCH" 0 ((3604.82647 2963.80090) (3601.35215 2952.49491) (3604.82647 2944.94695)))
("SF_MASONRY_AND_ARCH" 0 ((3608.59729 2326.54627) (3782.05136 2319.00452)))
("SF_MASONRY_AND_ARCH" 0 ((3608.59729 1331.07183) (3619.90950 1334.84163)))
("SF_PLANTING" 0 ((3634.99253 542.98643) (3608.59729 520.36199)))
("SF_PLANTING" 0 ((3612.36810 6874.05758) (3612.36810 6851.43314)))
("SF_PLANTING" 0 ((3616.13869 6881.59853) (3612.36810 6874.05758)))
("SF_PLANTING" 0 ((3676.47059 6847.66188) (3665.15837 6844.03971) (3627.45090 6844.03971) (3612.36810 6851.43314)))
("SF_MASONRY_AND_ARCH" 0 ((3612.36810 2420.81448) (3615.84242 2447.20939) (3612.36810 2458.52161)))
("SF_PLANTING" 0 ((3638.76312 267.72342) (3612.36810 290.34785)))
("SF_PLANTING" 0 ((3616.13869 6881.59853) (3616.13869 6915.53518)))
("SF_PLANTING" 0 ((3638.76312 6919.30645) (3616.13869 6915.53518)))
("SF_PLANTING" 0 ((3650.07534 6900.45249) (3638.76312 6890.33790) (3616.13869 6881.59853)))
("SF_MASONRY_AND_ARCH" 0 ((3616.13869 3182.50351) (3650.07534 3186.27477)))
("SF_MASONRY_AND_ARCH" 0 ((3981.90045 1251.88631) (3872.54943 1248.12059) (3834.84163 1255.64921) (3815.98835
1251.89118) (3657.61697 1249.31233) (3638.76312 1255.50837) (3616.13869 1255.65611)))
("SF_MASONRY_AND_ARCH" 0 ((3619.90950 1293.36256) (3616.28676 1285.81538) (3616.13869 1255.65611)))
("SF_PLANTING" 0 ((3642.53394 6983.40848) (3619.90950 6975.86753)))
("SF_PLANTING" 0 ((3646.30475 7077.67749) (3621.25554 7111.60724) (3623.68032 7119.15509)))
("SF_PLANTING" 0 ((3891.40271 814.47964) (3868.77828 799.54536) (3755.65611 799.39072) (3736.80249 795.78032)
(3691.55362 803.01968) (3623.68032 803.16742)))
("SF_MASONRY_AND_ARCH" 0 ((3631.22172 2243.58948) (3755.65611 2243.58326) (3774.50973 2239.82590) (3793.36391
2243.58948)))
("SF_PLANTING" 0 ((3638.76312 6919.30645) (3650.07534 6900.45249)))
("SF_PLANTING" 0 ((3638.76312 6919.30645) (3646.45294 6938.00520) (3657.61697 6941.93088)))
("SF_MASONRY_AND_ARCH" 0 ((3638.76312 3412.51912) (3672.69321 3412.67376) (3680.24140 3420.06007)))
("SF_MASONRY_AND_ARCH" 0 ((3638.76312 3337.10407) (3684.01199 3340.86143) (3699.09502 3337.25181) (3751.88529
3337.11029) (3774.50973 3340.87455) (3808.44604 3337.10407)))
("SF_PLANTING" 0 ((3638.76312 267.72342) (3638.76312 245.09898)))
("SF_PLANTING" 0 ((3638.76312 267.72342) (3661.38756 286.57523)))
("SF_PLANTING" 0 ((3691.55362 245.09898) (3638.76312 245.09898)))
("SF_PLANTING" 0 ((3691.55362 7002.26244) (3668.92262 6982.66176) (3642.53394 6983.40848)))
("SF_PLANTING" 0 ((3646.30475 7077.67749) (3642.53394 6983.40848)))
("SF_MASONRY_AND_ARCH" 0 ((3759.42692 1730.76923) (3748.11437 1734.39197) (3668.92919 1734.54593) (3642.53394
1738.31165)))
("SF_PLANTING" 0 ((3646.30475 7077.67749) (3657.61697 7081.44796)))
("SF_MASONRY_AND_ARCH" 0 ((3646.30475 2779.03495) (3733.03167 2775.27059) (3748.11471 2782.80543)))
("SF_PLANTING" 0 ((3661.38756 286.57523) (3661.23937 305.42986) (3647.35464 335.59672) (3646.30475 350.67873)))
("SF_PLANTING" 0 ((3646.30475 350.67873) (3628.65532 358.37443) (3628.65532 376.91968) (3634.99910 380.54174)
(3653.84615 373.30317)))
("SF_PLANTING" 0 ((3646.30475 350.67873) (3653.84615 373.30317)))
("SF_PLANTING" 0 ((3650.07534 6900.45249) (3676.47059 6896.68201)))
("SF_ARCHITECTURE" 0 ((3657.61697 3849.92500) (3653.85271 3861.23722) (3653.85271 4098.79378) (3657.61697 4121.41821)
(3657.61041 4935.89785) (3653.85271 4954.75113) (3653.85271 5177.22432) (3657.61041 5196.07885) (3657.61697 5395.92760)
(3653.84615 5426.09310)))
("SF_ARCHITECTURE" 0 ((3653.84615 5426.09310) (3638.76324 5441.17647) (3638.76324 5471.34197) (3650.21686 5486.27070)
(3657.61697 5490.19649)))
("SF_ARCHITECTURE" 0 ((3653.84615 5426.09310) (3672.69989 5444.94762) (3672.69989 5475.11312) (3657.61697 5490.19649)))
("SF_PLANTING" 0 ((3684.01199 380.84559) (3653.84615 373.30317)))
("SF_ARCHITECTURE" 0 ((3657.61697 5637.25498) (3657.61697 5490.19649)))
("SF_ARCHITECTURE" 0 ((3659.50226 5691.93054) (3647.51199 5682.50045) (3642.54050 5659.87941) (3643.73846 5648.56719)
(3657.61697 5637.25498)))
("SF_ARCHITECTURE" 0 ((3659.50226 5691.93054) (3672.69989 5678.73609) (3672.69989 5648.56719) (3657.61697 5637.25498)))
("SF_MASONRY_AND_ARCH" 0 ((3657.61697 2635.74661) (3676.47059 2639.36934) (3717.94864 2635.75283) (3740.57308
2639.51708) (3940.42274 2635.74661)))
("SF_MASONRY_AND_ARCH" 0 ((3657.61697 1157.61595) (3657.61697 1150.07636)))
("SF_ARCHITECTURE" 0 ((3659.50226 5691.93054) (3680.24140 5708.74412) (3702.86550 5708.74412) (3714.17805 5701.35747)))
("SF_MASONRY_AND_ARCH" 0 ((3661.38756 3186.27477) (3684.01199 3189.74910) (3699.09502 3186.28100) (3789.59276
3186.28100) (3819.75826 3190.04525) (3842.38269 3186.28100) (3872.54943 3190.03213) (3887.63156 3186.42319) (4000.75373
3190.04525)))
("SF_PLANTING" 0 ((3661.38756 286.57523) (3672.69977 285.37183) (3680.09333 279.02805) (3691.55362 256.41120)))
("SF_MASONRY_AND_ARCH" 0 ((3725.49027 1334.84163) (3714.17771 1338.46437) (3668.92919 1338.61143)))
("SF_PLANTING" 0 ((3880.09050 859.72851) (3699.09502 859.72229) (3684.01199 856.26041) (3668.92919 867.27093)))
("SF_PLANTING" 0 ((3680.24140 6885.36980) (3676.47059 6896.68201)))
("SF_PLANTING" 0 ((3717.94864 6957.01357) (3695.32455 6944.65192) (3685.21606 6934.38914) (3676.47059 6896.68201)))
("SF_PLANTING" 0 ((3676.47059 6847.66188) (3691.55362 6833.78348) (3710.40724 6828.80871)))
("SF_PLANTING" 0 ((3676.47059 6847.66188) (3676.61867 6877.82149) (3680.24140 6885.36980)))
("SF_MASONRY_AND_ARCH" 0 ((3676.47059 3054.29864) (3687.78281 3050.54129) (3702.86584 3054.15090) (3748.11471
3054.29864)))
("SF_PLANTING" 0 ((3680.24140 6885.36980) (3710.40724 6900.30419) (3736.80249 6899.40305) (3755.65611 6889.14027)))
("SF_PLANTING" 0 ((3702.86584 377.07296) (3684.01199 380.84559)))
("SF_PLANTING" 0 ((3684.01199 380.84559) (3687.78281 422.32183)))
("SF_PLANTING" 0 ((3702.86584 377.07296) (3706.34016 358.22115) (3697.89706 331.83167) (3684.01199 324.28450)))
("SF_ARCHITECTURE" 0 ((3687.78281 7658.37104) (3701.66143 7643.28812) (3702.86584 7631.97590)))
("SF_ARCHITECTURE" 0 ((3691.55362 7775.26391) (3687.78937 7760.18100) (3687.78281 7658.37104)))
("SF_ARCHITECTURE" 0 ((3687.78281 7616.89287) (3691.55351 7601.80995) (3691.55351 7088.98971) (3691.55351 7036.19910)
(3691.55362 7017.34514)))
("SF_ARCHITECTURE" 0 ((3687.78281 7616.89287) (3698.94038 7620.81821) (3702.86584 7631.97590)))
("SF_ARCHITECTURE" 0 ((3691.55362 7952.48869) (3710.40724 7952.48869) (3720.51493 7963.80102) (3726.54672 8005.27896)
(3750.68767 8035.44502) (3755.65611 8073.15238)))
("SF_ARCHITECTURE" 0 ((3691.55362 7952.48869) (3687.93744 7911.01052) (3691.40554 7895.92760) (3691.55362 7835.59581)))
("SF_SOLAR" 0 ((3691.55362 7835.59581) (4174.20814 7835.58925) (4193.06143 7831.83156) (4294.87138 7831.83156)
(4366.51584 7839.36652)))
("SF_ARCHITECTURE" 0 ((3691.55362 7835.59581) (3687.78281 7797.88835) (3691.55362 7775.26391)))
("SF_ARCHITECTURE" 0 ((7303.92183 7779.03473) (7292.60962 7775.27048) (3706.63643 7775.26391) (3691.55362 7775.26391)))
("SF_PLANTING" 0 ((3691.55362 7002.26244) (3691.55362 7017.34514)))
("SF_PLANTING" 0 ((3733.03167 7036.19910) (3725.34219 7022.32070) (3691.55362 7017.34514)))
("SF_PLANTING" 0 ((3717.94864 6972.09627) (3691.55362 7002.26244)))
("SF_PLANTING" 0 ((3691.55362 6730.76923) (3706.63643 6745.85192)))
("SF_PLANTING" 0 ((3691.55362 245.09898) (3691.55362 256.41120)))
("SF_PLANTING" 0 ((3691.55362 256.41120) (3733.03167 272.54955) (3751.88529 290.34785)))
("SF_PLANTING" 0 ((3691.55362 245.09898) (3714.17805 230.16256) (3804.67613 237.55656)))
("SF_ARCHITECTURE" 0 ((3702.86584 7631.97590) (4981.14672 7635.75317) (5003.77115 7639.51731) (5335.59536 7639.51075)
(5358.21980 7635.74661) (6425.33937 7635.75317) (6440.42206 7639.36923) (6504.52489 7639.51075) (6523.37885 7635.75317)
(7307.69231 7631.97590)))
("SF_PLANTING" 0 ((3725.49027 6708.14480) (3702.86584 6704.37432)))
("SF_PLANTING" 0 ((3710.40724 6644.04197) (3702.86584 6632.72975)))
("SF_MASONRY_AND_ARCH" 0 ((3702.86584 3476.62115) (3710.41380 3472.99842) (3778.28054 3472.85068)))
("SF_MASONRY_AND_ARCH" 0 ((3706.63643 3487.93337) (3702.86584 3476.62115)))
("SF_PLANTING" 0 ((3702.86584 377.07296) (3710.41380 380.54174) (3736.80249 369.68043) (3766.96833 369.53337)))
("SF_PLANTING" 0 ((3706.63643 6779.78857) (3751.88529 6776.01810)))
("SF_PLANTING" 0 ((3706.63643 6779.78857) (3710.40724 6828.80871)))
("SF_PLANTING" 0 ((3710.40724 6828.80871) (3720.66346 6836.49796) (3730.31719 6855.05532) (3747.96007 6870.28665)
(3755.65611 6889.14027)))
("SF_MASONRY_AND_ARCH" 0 ((3710.40724 3529.41176) (3725.49027 3525.64129) (3932.88043 3525.64751) (3963.04717
3529.41176)))
("SF_PLANTING" 0 ((3714.17805 6595.02262) (3721.71946 6602.56437)))
("SF_PLANTING" 0 ((3714.17805 6478.12975) (3736.80249 6478.12975)))
("SF_PLANTING" 0 ((3725.49027 6515.83710) (3715.38224 6508.28914) (3714.17805 6478.12975)))
("SF_ARCHITECTURE" 0 ((3740.57308 5701.35747) (3714.17805 5701.35747)))
("SF_ARCHITECTURE" 0 ((3725.49027 5652.33778) (3710.56188 5671.19163) (3710.55532 5693.80950) (3714.17805 5701.35747)))
("SF_PLANTING" 0 ((3717.94864 6972.09627) (3717.94864 6957.01357)))
("SF_PLANTING" 0 ((3717.94864 6972.09627) (3748.10814 6997.28767) (3755.65611 6998.49197)))
("SF_PLANTING" 0 ((3785.82161 6911.76471) (3774.36154 6933.33314) (3717.94864 6957.01357)))
("SF_MASONRY_AND_ARCH" 0 ((3717.94864 1990.95023) (3718.09672 2036.19910) (3721.71946 2051.28179)))
("SF_PLANTING" 0 ((3793.36391 7039.96957) (3792.99491 7047.14932) (3770.73914 7048.71561) (3744.34389 7077.52919)
(3721.71946 7088.98971)))
("SF_MASONRY_AND_ARCH" 0 ((3800.90498 2058.82353) (3793.35701 2055.20079) (3733.03167 2054.90532) (3721.71946
2051.28179)))
("SF_PLANTING" 0 ((3736.80249 595.77771) (3721.71946 599.54751)))
("SF_PLANTING" 0 ((3757.54140 6696.83258) (3725.49027 6708.14480)))
("SF_PLANTING" 0 ((3748.11471 6738.31097) (3733.18631 6730.76267) (3725.49027 6708.14480)))
("SF_PLANTING" 0 ((3725.49027 6515.83710) (3751.88529 6512.22093) (3761.99299 6519.61448) (3758.22907 6542.22545)
(3744.34389 6549.77376)))
("SF_PLANTING" 0 ((3725.49027 6515.83710) (3730.46493 6538.46154) (3744.34389 6549.77376)))
("SF_ARCHITECTURE" 0 ((3725.49027 5652.33778) (3725.63846 5592.00645) (3729.26086 5573.15192) (3729.25430 4159.12477)
(3725.49683 4140.27149) (3725.49683 3932.88043) (3729.11267 3917.79830) (3729.41550 3857.46606) (3748.11459
3838.61278)))
("SF_ARCHITECTURE" 0 ((3740.57308 5701.35747) (3739.36889 5667.42081) (3725.49027 5652.33778)))
("SF_MASONRY_AND_ARCH" 0 ((3736.80249 1070.89084) (3726.69446 1082.20305) (3725.49027 1104.82749)))
("SF_MASONRY_AND_ARCH" 0 ((4098.79378 1074.66063) (3993.21267 1074.80905) (3978.28428 1082.35011) (3973.15464
1100.90158) (3966.81086 1104.67217) (3910.25600 1108.59729) (3853.69491 1108.44955) (3838.61278 1104.83993) (3823.52941
1108.44955) (3755.65611 1108.59106) (3725.49027 1104.82749)))
("SF_MASONRY_AND_ARCH" 0 ((3751.88529 2092.76018) (3729.26086 2092.76018)))
("SF_MASONRY_AND_ARCH" 0 ((3729.26086 995.47511) (3725.49027 1014.32975) (3729.26086 1033.18156)))
("SF_MASONRY_AND_ARCH" 0 ((3729.26086 995.47511) (3748.11471 991.71018) (3861.23722 991.71018) (3876.31934 995.17274)
(3898.94378 980.54638) (3989.44152 980.39796) (4012.06595 984.16290) (4038.46154 980.39310)))
("SF_PLANTING" 0 ((3804.67613 6579.93993) (3781.89672 6639.06697) (3766.97489 6637.39559) (3748.11437 6618.70305)
(3733.03167 6613.87658)))
("SF_PLANTING" 0 ((3733.03167 6451.73462) (3736.80249 6478.12975)))
("SF_PLANTING" 0 ((3914.02715 6478.12964) (3887.63156 6478.12975) (3748.11471 6478.12975) (3736.80249 6478.12975)))
("SF_PLANTING" 0 ((3793.36391 426.09446) (3785.96346 430.01889) (3774.36154 447.52025) (3755.65611 456.40690)
(3736.80249 478.88292)))
("SF_PLANTING" 0 ((3744.34389 493.96776) (3736.80249 478.88292)))
("SF_ARCHITECTURE" 0 ((3740.57308 7571.64400) (3755.65611 7571.64400) (4362.74468 7571.64400) (4377.82805 7571.64400)))
("SF_ARCHITECTURE" 0 ((3740.57308 5701.35747) (3751.88563 5708.74412) (3778.28054 5708.75068) (3789.43812 5704.07195)
(3793.35701 5693.81572) (3797.13428 3849.92500) (3800.75690 3823.52941) (3800.90498 3797.13382)))
("SF_PLANTING" 0 ((3748.11471 316.74208) (3740.57308 320.51188)))
("SF_PLANTING" 0 ((3759.42692 6595.02262) (3745.40023 6568.62771) (3744.34389 6549.77376)))
("SF_PLANTING" 0 ((3748.11471 6738.31097) (3763.19751 6726.99876)))
("SF_PLANTING" 0 ((3748.11471 6738.31097) (3751.88529 6776.01810)))
("SF_PLANTING" 0 ((3748.11471 6662.89593) (3749.16459 6681.74989) (3757.54140 6696.83258)))
("SF_MASONRY_AND_ARCH" 0 ((3748.11471 3054.29864) (3766.96833 3050.53439) (3970.58824 3050.37353) (3996.98382
3039.21595)))
("SF_MASONRY_AND_ARCH" 0 ((3751.88529 3073.15260) (3748.11471 3054.29864)))
("SF_MASONRY_AND_ARCH" 0 ((3985.67161 1598.79242) (3974.35871 1602.55814) (3782.05136 1602.71210) (3748.11471
1613.87726)))
("SF_MASONRY_AND_ARCH" 0 ((3751.88529 1636.50170) (3748.11471 1613.87726)))
("SF_PLANTING" 0 ((3748.11471 316.74208) (3751.88529 290.34785)))
("SF_PLANTING" 0 ((3748.11471 316.74208) (3755.65611 320.51188)))
("SF_PLANTING" 0 ((3782.05136 6776.01810) (3751.88529 6776.01810)))
("SF_PLANTING" 0 ((3751.88529 6776.01810) (3752.03993 6806.18394) (3763.19751 6817.49649)))
("SF_MASONRY_AND_ARCH" 0 ((3891.40271 1440.42138) (3876.31934 1436.79932) (3751.88529 1432.88179)))
("SF_MASONRY_AND_ARCH" 0 ((3751.88529 1338.61143) (3774.50973 1334.84785) (3861.23722 1334.84785) (3925.33937
1342.37647) (4019.60826 1334.84163)))
("SF_PLANTING" 0 ((3766.96833 369.53337) (3765.76414 388.38518) (3751.88529 407.23982)))
("SF_PLANTING" 0 ((3751.88529 290.34785) (3812.21719 297.88744)))
("SF_PLANTING" 0 ((3755.65611 6998.49197) (3763.35215 6983.41538) (3774.50973 6975.86753)))
("SF_PLANTING" 0 ((3755.65611 6998.49197) (3763.20407 7008.59989) (3778.28054 7009.79762) (3804.52115 6997.29423)
(3812.21719 6960.78405)))
("SF_PLANTING" 0 ((3785.82161 6911.76471) (3774.50973 6897.73801) (3755.65611 6889.14027)))
("SF_PLANTING" 0 ((3757.54140 6696.83258) (3800.90498 6696.83258)))
("SF_PLANTING" 0 ((3757.54140 6696.83258) (3763.04627 6708.14480) (3763.19751 6726.99876)))
("SF_MASONRY_AND_ARCH" 0 ((3785.82161 3148.56686) (3778.12590 3130.91776) (3759.42692 3125.94242)))
("SF_MASONRY_AND_ARCH" 0 ((3759.42692 1730.76923) (3755.80419 1719.45701) (3756.86063 1681.75057) (3766.96833
1671.64174) (3782.05136 1674.20814)))
("SF_MASONRY_AND_ARCH" 0 ((3797.13382 1742.08145) (3785.82161 1735.59615) (3759.42692 1730.76923)))
("SF_PLANTING" 0 ((3782.05136 6776.01810) (3780.84695 6806.02941) (3767.12296 6811.15238) (3763.19751 6817.49649)))
("SF_PLANTING" 0 ((3763.19751 6817.49649) (3768.16629 6836.34966) (3778.28054 6846.60588) (3812.21719 6865.45984)
(3834.84163 6870.28631)))
("SF_PLANTING" 0 ((3797.13382 6734.53971) (3763.19751 6726.99876)))
("SF_PLANTING" 0 ((3766.96833 7104.07240) (3770.73914 7138.00905)))
("SF_PLANTING" 0 ((3812.21719 343.13631) (3789.59276 348.11233) (3766.96833 369.53337)))
("SF_MASONRY_AND_ARCH" 0 ((3800.90498 2058.82353) (3799.70045 2088.83507) (3793.35701 2092.60554) (3770.73914
2092.76018)))
("SF_MASONRY_AND_ARCH" 0 ((3778.28054 3472.85068) (3865.00713 3472.84446) (3887.63156 3469.08020) (3936.65158
3472.85068)))
("SF_MASONRY_AND_ARCH" 0 ((3778.28054 3472.85068) (3782.05136 3487.93337)))
("SF_MASONRY_AND_ARCH" 0 ((4000.75373 3103.31799) (3891.40271 3103.31176) (3868.77828 3099.54751) (3797.13382
3099.69525) (3778.28054 3103.31799)))
("SF_MASONRY_AND_ARCH" 0 ((3838.61278 1070.89084) (3778.28054 1070.89084)))
("SF_PLANTING" 0 ((3793.36391 6776.01810) (3782.05136 6776.01810)))
("SF_MASONRY_AND_ARCH" 0 ((4038.46154 2518.85396) (4035.88824 2466.06335) (4042.08428 2424.58495) (4030.91357
2406.93586) (3985.67161 2403.15848) (3929.11052 2409.35452) (3849.92500 2409.49604) (3782.05136 2401.96052)))
("SF_MASONRY_AND_ARCH" 0 ((3797.13382 2315.23405) (3793.36391 2319.00452) (3782.05136 2319.00452)))
("SF_MASONRY_AND_ARCH" 0 ((3785.82161 2352.94118) (3782.05136 2319.00452)))
("SF_PLANTING" 0 ((3785.82161 6911.76471) (3834.84163 6911.76471)))
("SF_PLANTING" 0 ((3793.36391 6957.01357) (3812.21719 6960.78405)))
("SF_PLANTING" 0 ((3797.13382 6734.53971) (3793.36391 6776.01810)))
("SF_PLANTING" 0 ((3793.36391 6776.01810) (3831.07048 6779.78857)))
("SF_MASONRY_AND_ARCH" 0 ((3823.52941 2775.26369) (3804.67613 2774.20735) (3793.36391 2767.72274)))
("SF_MASONRY_AND_ARCH" 0 ((3996.98382 2714.93213) (3989.43529 2711.30939) (3955.50486 2711.16165) (3932.88043
2714.92590) (3804.67613 2715.08676) (3793.36391 2726.24434)))
("SF_MASONRY_AND_ARCH" 0 ((3797.13382 1742.08145) (3793.36391 1760.93609)))
("SF_PLANTING" 0 ((3800.90498 592.00509) (3793.36391 588.23529)))
("SF_PLANTING" 0 ((3815.98835 384.61538) (3805.73156 388.54050) (3793.36391 426.09446)))
("SF_PLANTING" 0 ((3804.67613 444.94627) (3803.47138 433.64163) (3793.36391 426.09446)))
("SF_PLANTING" 0 ((3797.13382 6734.53971) (3804.67613 6734.53971)))
("SF_MASONRY_AND_ARCH" 0 ((3797.13382 2288.83835) (3797.13382 2315.23405)))
("SF_MASONRY_AND_ARCH" 0 ((3797.13382 2315.23405) (3812.21719 2318.99830) (3970.58824 2319.15226) (3981.90045
2322.77500)))
("SF_MASONRY_AND_ARCH" 0 ((3797.13382 1742.08145) (3812.21719 1738.31652) (3914.02093 1740.72817) (3921.42036
1730.76923) (3924.14174 1719.46391) (3921.56821 1711.91459)))
("SF_PLANTING" 0 ((3823.52941 6693.06210) (3800.90498 6696.83258)))
("SF_PLANTING" 0 ((3804.67613 6734.53971) (3800.90498 6696.83258)))
("SF_ARCHITECTURE" 0 ((3951.73495 3797.13382) (3929.11052 3793.36391) (3819.75826 3793.37014) (3800.90498 3797.13382)))
("SF_MASONRY_AND_ARCH" 0 ((3959.27602 2055.05305) (3812.21719 2055.05928) (3800.90498 2058.82353)))
("SF_MASONRY_AND_ARCH" 0 ((3800.90498 1821.26697) (3800.90498 1828.80871)))
("SF_MASONRY_AND_ARCH" 0 ((3815.98835 1817.49717) (3800.90498 1821.26697)))
("SF_MASONRY_AND_ARCH" 0 ((3868.77828 1670.43835) (3800.90498 1670.43835)))
("SF_PLANTING" 0 ((3800.90498 592.00509) (3815.98835 588.24152) (3981.90045 588.24152) (4004.52489 599.54751)))
("SF_PLANTING" 0 ((3800.90498 592.00509) (3804.67613 599.54751)))
("SF_PLANTING" 0 ((3823.52941 6738.31097) (3804.67613 6734.53971)))
("SF_ARCHITECTURE" 0 ((3804.67613 5829.56267) (3804.67613 5799.39661)))
("SF_ARCHITECTURE" 0 ((3955.50486 5833.33326) (3936.65158 5829.56267) (3815.98835 5833.32670) (3804.67613 5829.56267)))
("SF_ARCHITECTURE" 0 ((3955.50486 5799.39661) (3936.65158 5795.62602) (3838.61278 5795.63258) (3804.67613 5799.39661)))
("SF_PLANTING" 0 ((3859.35102 250.75509) (3838.61278 234.84242) (3812.22342 233.93382) (3804.67613 237.55656)))
("SF_PLANTING" 0 ((3804.67613 237.55656) (3804.82398 260.18100) (3812.21719 279.03563)))
("SF_MASONRY_AND_ARCH" 0 ((3808.44604 3337.10407) (3812.21719 3310.70916)))
("SF_PLANTING" 0 ((3808.44604 3337.10407) (3823.52941 3340.72681) (3947.96380 3340.88077) (3966.81708 3344.63269)
(3981.90045 3340.87455)))
("SF_PLANTING" 0 ((3819.75826 7073.90622) (3812.21719 7062.59400)))
("SF_PLANTING" 0 ((3838.61278 6941.93088) (3819.76516 6959.57975) (3812.21719 6960.78405)))
("SF_MASONRY_AND_ARCH" 0 ((3921.56821 2975.11312) (3812.21719 2967.57138)))
("SF_PLANTING" 0 ((3815.98835 324.28450) (3812.21719 343.13631)))
("SF_PLANTING" 0 ((3812.21719 343.13631) (3815.98835 384.61538)))
("SF_PLANTING" 0 ((3812.21719 279.03563) (3812.21719 297.88744)))
("SF_PLANTING" 0 ((3815.98835 324.28450) (3812.21719 297.88744)))
("SF_PLANTING" 0 ((3859.35102 250.75509) (3842.23484 270.28835) (3812.21719 279.03563)))
("SF_PLANTING" 0 ((3831.07048 422.32183) (3826.09581 388.54050) (3815.98835 384.61538)))
("SF_PLANTING" 0 ((3815.98835 324.28450) (3865.00713 324.28450)))
("SF_MASONRY_AND_ARCH" 0 ((3849.92500 2828.05430) (3819.75826 2828.05430)))
("SF_PLANTING" 0 ((3827.30057 7039.96957) (3823.52941 7051.28179)))
("SF_PLANTING" 0 ((3831.07048 6779.78857) (3861.23722 6779.78857)))
("SF_PLANTING" 0 ((3842.38269 6866.51584) (3838.45781 6817.49649) (3827.59649 6791.10113) (3831.07048 6779.78857)))
("SF_PLANTING" 0 ((3834.84163 6911.76471) (3834.84163 6870.28631)))
("SF_PLANTING" 0 ((3838.61278 6919.30645) (3834.84163 6911.76471)))
("SF_PLANTING" 0 ((3842.38269 6866.51584) (3834.84163 6870.28631)))
("SF_PLANTING" 0 ((3838.61278 6919.30645) (3838.61278 6941.93088)))
("SF_PLANTING" 0 ((3838.61278 6941.93088) (3849.92500 6949.47183)))
("SF_PLANTING" 0 ((3838.61278 6919.30645) (3849.92500 6915.68348) (3898.94378 6915.53518)))
("SF_MASONRY_AND_ARCH" 0 ((3838.61278 2775.26369) (3887.62534 2775.41143) (3895.17387 2779.03495)))
("SF_PLANTING" 0 ((3842.38269 6866.51584) (3902.71493 6874.05758)))
("SF_MASONRY_AND_ARCH" 0 ((3842.38269 2096.53066) (3887.63156 2100.14729) (3914.02715 2096.53066)))
("SF_MASONRY_AND_ARCH" 0 ((4004.52489 1813.72455) (3842.38269 1817.49717)))
("SF_PLANTING" 0 ((3849.92500 441.17647) (3842.38269 437.40667)))
("SF_PLANTING" 0 ((3849.92500 7021.11640) (3857.46606 6987.17975) (3849.92500 6949.47183)))
("SF_PLANTING" 0 ((3900.82998 6957.01357) (3880.09050 6956.86527) (3849.92500 6949.47183)))
("SF_PLANTING" 0 ((3849.92500 441.17647) (3856.26844 433.62919) (3857.46606 418.55204)))
("SF_PLANTING" 0 ((3849.92500 441.17647) (3850.97455 456.25848) (3858.52274 475.11312) (3868.77828 485.21425)
(3880.09050 482.65554)))
("SF_PLANTING" 0 ((3853.69491 6726.99876) (3861.24344 6730.62093) (3883.86165 6730.76923)))
("SF_PLANTING" 0 ((3883.86165 6730.76923) (3882.80498 6719.45701) (3876.17149 6708.29966) (3853.69491 6704.37432)))
("SF_ARCHITECTURE" 0 ((3936.65158 5625.94276) (3853.69491 5625.94276)))
("SF_ARCHITECTURE" 0 ((3857.46606 5708.89887) (3936.64536 5709.04695) (3944.19265 5712.66968)))
("SF_ARCHITECTURE" 0 ((3857.46606 4475.86686) (3883.86165 4475.71290) (3898.94378 4464.55464)))
("SF_MASONRY_AND_ARCH" 0 ((3857.46606 1070.89084) (3929.11052 1074.66063)))
("SF_PLANTING" 0 ((3859.35102 250.75509) (3887.63156 237.70498) (3932.88043 237.55656)))
("SF_PLANTING" 0 ((3859.35102 250.75509) (3878.88597 271.49321) (3880.09050 286.57523)))
("SF_PLANTING" 0 ((3861.23722 6779.78857) (3861.23722 6813.72523)))
("SF_PLANTING" 0 ((3902.71493 6776.01810) (3861.23722 6779.78857)))
("SF_PLANTING" 0 ((3872.54943 6553.54423) (3861.23722 6557.31550)))
("SF_ARCHITECTURE" 0 ((3861.23722 5584.46414) (3914.02715 5588.23529) (4068.62704 5588.22907) (4083.71041 5584.46414)))
("SF_ARCHITECTURE" 0 ((3861.23722 4453.24242) (3887.63156 4454.44717) (3898.94378 4464.55464)))
("SF_PLANTING" 0 ((3865.00713 7055.05305) (3866.53088 7062.60090) (3857.76256 7092.76018) (3866.06380 7115.37805)
(3876.31934 7122.92636)))
("SF_PLANTING" 0 ((3865.00713 6410.25633) (3871.49276 6421.56889) (3872.54943 6440.42240)))
("SF_PLANTING" 0 ((3865.00713 324.28450) (3880.09050 286.57523)))
("SF_PLANTING" 0 ((3865.00713 324.28450) (3872.54943 335.59672) (3876.31934 335.59672)))
("SF_PLANTING" 0 ((3880.09050 6644.04197) (3880.09050 6647.81324) (3868.77828 6655.35419)))
("SF_PLANTING" 0 ((3880.09050 6644.04197) (3878.88597 6632.72975) (3868.77828 6622.62839) (3853.84989 6626.24480)
(3848.26007 6640.27149) (3850.98733 6647.65837) (3868.77828 6655.35419)))
("SF_PLANTING" 0 ((3872.54943 6662.89593) (3868.77828 6655.35419)))
("SF_PLANTING" 0 ((3872.54943 6553.54423) (3873.75328 6546.00328) (3883.86165 6538.46154)))
("SF_PLANTING" 0 ((3895.17387 6579.93993) (3876.47432 6568.62115) (3872.54943 6553.54423)))
("SF_PLANTING" 0 ((3876.31934 773.00057) (3883.86165 773.00057)))
("SF_PLANTING" 0 ((3876.31934 335.59672) (3917.79830 328.05430)))
("SF_PLANTING" 0 ((3876.31934 335.59672) (3876.46776 369.53337) (3881.14717 392.15781) (3895.17387 411.00962)))
("SF_PLANTING" 0 ((3880.09050 6644.04197) (3891.40271 6647.81324)))
("SF_PLANTING" 0 ((3880.09050 859.72851) (3887.63156 840.87387)))
("SF_MASONRY_AND_ARCH" 0 ((3880.09050 859.72851) (3891.24808 878.58314) (3891.40271 938.91403)))
("SF_PLANTING" 0 ((3932.88043 237.55656) (3917.79140 267.57500) (3895.17387 283.70023) (3880.09050 286.57523)))
("SF_PLANTING" 0 ((3932.88043 7062.59400) (3883.86165 7013.57466)))
("SF_PLANTING" 0 ((3895.17387 6730.76923) (3883.86165 6730.76923)))
("SF_PLANTING" 0 ((3883.86165 6523.37885) (3880.09050 6527.14932) (3883.86165 6538.46154)))
("SF_PLANTING" 0 ((3883.86165 6538.46154) (3898.93756 6543.28880) (3905.28133 6549.78032) (3906.48609 6576.16867)))
("SF_PLANTING" 0 ((3891.40271 814.47964) (3887.63156 829.56165)))
("SF_PLANTING" 0 ((3891.40271 6828.80871) (3899.09876 6809.95475) (3914.02715 6798.64253)))
("SF_MASONRY_AND_ARCH" 0 ((3891.40271 1440.42138) (3906.48609 1433.02952) (3978.12930 1434.55260) (4049.77376
1429.10916)))
("SF_MASONRY_AND_ARCH" 0 ((3891.40271 1440.42138) (3895.17387 1466.81844)))
("SF_PLANTING" 0 ((4162.89593 806.93722) (4106.33484 807.08563) (4079.93925 814.47342) (4004.52489 810.70984)
(3978.12930 814.47964) (3925.33937 814.33190) (3906.48609 810.71606) (3891.40271 814.47964)))
("SF_PLANTING" 0 ((3895.17387 6730.76923) (3917.79830 6726.99876)))
("SF_PLANTING" 0 ((3895.17387 6730.76923) (3895.32172 6757.16414) (3902.71493 6776.01810)))
("SF_PLANTING" 0 ((3895.17387 6579.93993) (3906.48609 6576.16867)))
("SF_PLANTING" 0 ((3895.17387 6579.93993) (3899.99423 6595.02262) (3911.30577 6613.72172) (3917.79830 6617.64706)))
("SF_PLANTING" 0 ((3895.17387 6293.36357) (3914.02715 6300.90498)))
("SF_PLANTING" 0 ((3929.11052 395.92760) (3895.17387 411.00962)))
("SF_PLANTING" 0 ((3929.11052 441.17647) (3899.09876 439.97161) (3895.32783 433.62919) (3895.17387 411.00962)))
("SF_PLANTING" 0 ((3898.94378 6915.53518) (3902.71493 6907.99423)))
("SF_PLANTING" 0 ((3898.94378 6915.53518) (3900.82998 6957.01357)))
("SF_ARCHITECTURE" 0 ((4113.87590 4453.24242) (4091.25147 4468.17115) (3898.94378 4464.55464)))
("SF_MASONRY_AND_ARCH" 0 ((3974.35939 1523.37952) (3970.43360 1529.87036) (3959.27602 1534.54333) (3906.49231
1533.16719) (3898.94378 1538.46154)))
("SF_PLANTING" 0 ((3900.82998 6957.01357) (3925.33937 6957.01357)))
("SF_PLANTING" 0 ((3900.82998 6957.01357) (3903.91946 6975.86753) (3939.36606 7009.95170) (3947.96380 7024.88688)))
("SF_PLANTING" 0 ((3902.71493 6874.05758) (3902.71493 6907.99423)))
("SF_PLANTING" 0 ((3936.65158 6934.38914) (3928.96210 6919.46052) (3902.71493 6907.99423)))
("SF_PLANTING" 0 ((3942.30769 6857.08925) (3929.11301 6865.45633) (3906.64005 6867.71357) (3902.71493 6874.05758)))
("SF_PLANTING" 0 ((3915.91210 6777.90373) (3902.71493 6776.01810)))
("SF_PLANTING" 0 ((3915.91210 6355.58077) (3902.71493 6349.92466)))
("SF_PLANTING" 0 ((3932.88043 6579.93993) (3906.48609 6576.16867)))
("SF_MASONRY_AND_ARCH" 0 ((3917.79830 1666.66572) (3906.48609 1670.43835)))
("SF_PLANTING" 0 ((3915.91210 6777.90373) (3914.02715 6798.64253)))
("SF_PLANTING" 0 ((3942.30769 6857.08925) (3931.98903 6847.65882) (3924.13518 6809.95475) (3914.02715 6798.64253)))
("SF_PLANTING" 0 ((3914.02715 6478.12964) (3921.56821 6478.12964)))
("SF_PLANTING" 0 ((3914.02715 6478.12964) (3917.79830 6512.06629)))
("SF_PLANTING" 0 ((3921.56821 6278.28054) (3923.98744 6289.59276) (3914.02715 6300.90498)))
("SF_PLANTING" 0 ((3915.91210 6355.58077) (3917.79140 6323.52941) (3914.02715 6300.90498)))
("SF_PLANTING" 0 ((3914.02715 6248.11471) (3917.79830 6206.63643)))
("SF_PLANTING" 0 ((3915.91210 6777.90373) (3927.90260 6764.70894) (3929.11052 6734.53971)))
("SF_PLANTING" 0 ((3915.91210 6777.90373) (3970.58824 6779.78857)))
("SF_PLANTING" 0 ((3915.91210 6355.58077) (3936.65158 6353.69525)))
("SF_PLANTING" 0 ((3915.91210 6355.58077) (3917.64989 6372.54910) (3911.45385 6406.48575) (3914.17523 6440.42240)
(3921.56821 6463.04683)))
("SF_PLANTING" 0 ((3917.79830 6726.99876) (3917.94615 6700.60995) (3921.56821 6693.06210)))
("SF_PLANTING" 0 ((3917.79830 6726.99876) (3929.11052 6734.53971)))
("SF_PLANTING" 0 ((3932.88043 6579.93993) (3924.14174 6610.09876) (3917.79830 6617.64706)))
("SF_PLANTING" 0 ((3917.79830 6617.64706) (3925.33937 6636.50102)))
("SF_MASONRY_AND_ARCH" 0 ((3917.79830 2507.54174) (3924.14174 2503.61584) (3929.11052 2473.60509)))
("SF_PLANTING" 0 ((3921.56821 320.51188) (3917.79830 328.05430)))
("SF_PLANTING" 0 ((3917.79830 328.05430) (3947.96380 339.36652)))
("SF_PLANTING" 0 ((3925.33937 6636.50102) (3914.17523 6666.66640) (3915.22477 6681.74955) (3921.56821 6693.06210)))
("SF_PLANTING" 0 ((3951.73495 6726.99876) (3946.75962 6704.52217) (3921.56821 6693.06210)))
("SF_PLANTING" 0 ((3921.56821 6478.12964) (3921.56821 6463.04683)))
("SF_PLANTING" 0 ((3947.96380 6481.90045) (3921.56821 6478.12964)))
("SF_PLANTING" 0 ((3966.81708 6402.71493) (3946.90713 6440.42240) (3921.56821 6463.04683)))
("SF_PLANTING" 0 ((3936.65158 6934.38914) (3925.33937 6957.01357)))
("SF_PLANTING" 0 ((3951.73495 6987.17975) (3925.33937 6957.01357)))
("SF_PLANTING" 0 ((3959.27602 6640.27149) (3925.33937 6636.50102)))
("SF_PLANTING" 0 ((3929.11052 6734.53971) (3951.73495 6726.99876)))
("SF_PLANTING" 0 ((3929.11052 3717.94830) (3944.03869 3722.77613) (3947.80260 3729.26742) (3946.75928 3736.80215)
(3936.65158 3748.11505)))
("SF_PLANTING" 0 ((3936.65158 403.47002) (3929.11052 441.17647)))
("SF_PLANTING" 0 ((3929.11052 441.17647) (3944.19265 444.79853) (3959.12794 437.25826) (3973.15464 418.55204)
(3974.35939 388.38518)))
("SF_PLANTING" 0 ((3947.96380 339.36652) (3930.30781 380.84559) (3929.11052 395.92760)))
("SF_PLANTING" 0 ((3936.65158 403.47002) (3929.11052 395.92760)))
("SF_PLANTING" 0 ((3932.88043 6579.93993) (3940.26776 6572.39163) (3940.42274 6542.23201)))
("SF_PLANTING" 0 ((3932.88043 237.55656) (3944.19333 233.93382) (3981.90045 233.93450) (4004.52489 245.09898)))
("SF_PLANTING" 0 ((3936.65158 6934.38914) (3974.35939 6934.38914)))
("SF_PLANTING" 0 ((3936.65158 3472.85068) (3936.65158 3484.16290)))
("SF_PLANTING" 0 ((3936.65158 3472.85068) (3947.96380 3469.22794) (3981.90045 3469.08020)))
("SF_PLANTING" 0 ((3936.65158 403.47002) (3963.04649 389.44231) (3974.35939 388.38518)))
("SF_MASONRY_AND_ARCH" 0 ((3947.96380 2782.80543) (3940.42274 2779.03495)))
("SF_PLANTING" 0 ((4008.29604 6832.57919) (3993.21267 6842.69367) (3966.81708 6851.28484) (3951.66731 6851.65486)
(3942.30769 6857.08925)))
("SF_PLANTING" 0 ((3942.30769 6857.08925) (3959.43066 6889.13371) (3981.90045 6900.45249)))
("SF_PLANTING" 0 ((4008.29604 6481.90045) (3947.96380 6481.90045)))
("SF_PLANTING" 0 ((3947.96380 6481.90045) (3951.73495 6504.52489)))
("SF_MASONRY_AND_ARCH" 0 ((4057.31482 2775.26369) (4042.23269 2778.88722) (3959.27602 2779.18269) (3947.96380
2782.80543)))
("SF_MASONRY_AND_ARCH" 0 ((3947.96380 2782.80543) (3944.34106 2805.42986) (3955.50486 2828.05430)))
("SF_PLANTING" 0 ((3989.44152 335.59672) (3947.96380 339.36652)))
("SF_PLANTING" 0 ((3974.35939 6726.99876) (3951.73495 6726.99876)))
("SF_PLANTING" 0 ((3951.73495 3797.13382) (3989.44152 3796.98597) (4000.75373 3793.36391)))
("SF_PLANTING" 0 ((4038.46154 3883.86165) (4033.49310 3868.78450) (4027.14310 3862.29333) (3981.90045 3841.18541)
(3963.19502 3827.15215) (3952.79038 3808.44672) (3951.73495 3797.13382)))
("SF_PLANTING" 0 ((3951.73495 3318.25011) (3955.50486 3303.16742)))
("SF_MASONRY_AND_ARCH" 0 ((3955.50486 1659.12613) (4019.60826 1655.35351)))
("SF_PLANTING" 0 ((3985.67161 6587.48088) (3959.27602 6640.27149)))
("SF_PLANTING" 0 ((4000.75373 6696.83258) (3975.56324 6681.74299) (3973.15464 6659.12545) (3959.27602 6640.27149)))
("SF_MASONRY_AND_ARCH" 0 ((3959.27602 2055.05305) (3959.43066 2009.80419) (3966.81708 1998.49197)))
("SF_MASONRY_AND_ARCH" 0 ((3959.27602 2055.05305) (3955.80826 2092.75396) (3959.43066 2099.24548) (3970.58824
2103.92398) (4166.66708 2104.06618) (4181.74921 2100.30192)))
("SF_PLANTING" 0 ((3963.04717 7055.05305) (3964.10260 7066.36527) (3974.35939 7085.21844)))
("SF_PLANTING" 0 ((3970.58824 6779.78857) (3970.44016 6798.64253) (3963.04717 6817.49649)))
("SF_MASONRY_AND_ARCH" 0 ((3985.67161 2522.62443) (3978.12308 2516.28066) (3966.81708 2515.08269)))
("SF_MASONRY_AND_ARCH" 0 ((3966.81708 1742.08145) (4061.08597 1742.08145)))
("SF_PLANTING" 0 ((4008.29604 6753.39367) (3993.21267 6758.36188) (3970.58824 6779.78857)))
("SF_MASONRY_AND_ARCH" 0 ((3970.58824 2971.34265) (3985.67161 2982.65486)))
("SF_PLANTING" 0 ((4032.80543 461.91459) (4000.75373 463.94932) (3981.90045 471.33575) (3970.58824 471.34333)))
("SF_PLANTING" 0 ((3985.67161 6926.84740) (3974.35939 6934.38914)))
("SF_PLANTING" 0 ((3974.35939 6934.38914) (3989.44152 6998.49197)))
("SF_PLANTING" 0 ((4038.46154 3883.86165) (4037.25701 3891.25464) (4030.91357 3895.01889) (3993.21267 3895.02545)
(3974.35939 3887.63156)))
("SF_PLANTING" 0 ((3974.35939 3763.19717) (3996.98382 3770.73948)))
("SF_MASONRY_AND_ARCH" 0 ((3981.90045 1240.57410) (3981.74581 1187.78281) (3974.35939 1176.47059)))
("SF_PLANTING" 0 ((3974.35939 388.38518) (3989.44152 346.90894)))
("SF_MASONRY_AND_ARCH" 0 ((3978.12930 1568.62839) (3985.67161 1598.79242)))
("SF_PLANTING" 0 ((3989.44152 6892.91075) (3981.90045 6900.45249)))
("SF_PLANTING" 0 ((3985.67161 6926.84740) (3981.90045 6900.45249)))
("SF_MASONRY_AND_ARCH" 0 ((3981.90045 2673.45373) (3979.33405 2635.74661) (3985.67161 2620.66391)))
("SF_MASONRY_AND_ARCH" 0 ((3985.67161 2522.62443) (3981.90045 2575.41505)))
("SF_MASONRY_AND_ARCH" 0 ((3981.90045 2322.77500) (3981.90045 2345.39943)))
("SF_MASONRY_AND_ARCH" 0 ((4204.37364 2322.77500) (4193.06143 2319.15226) (4140.27149 2316.43190) (4106.33484
2318.99830) (4091.25147 2315.38869) (4072.39819 2318.99830) (3989.44842 2319.15226) (3981.90045 2322.77500)))
("SF_MASONRY_AND_ARCH" 0 ((3981.90045 1240.57410) (3981.90045 1251.88631)))
("SF_MASONRY_AND_ARCH" 0 ((3981.90045 1251.88631) (3985.67161 1270.73812)))
("SF_MASONRY_AND_ARCH" 0 ((3981.90045 1240.57410) (4019.60826 1236.80147)))
("SF_PLANTING" 0 ((3985.67161 6926.84740) (4000.75373 6926.84740)))
("SF_MASONRY_AND_ARCH" 0 ((3985.67161 2522.62443) (4038.46154 2518.85396)))
("SF_MASONRY_AND_ARCH" 0 ((3985.67161 2375.56561) (3985.67161 2368.02387)))
("SF_MASONRY_AND_ARCH" 0 ((4087.48156 1598.79242) (3985.67161 1598.79242)))
("SF_MASONRY_AND_ARCH" 0 ((4012.06595 1308.44740) (3985.67161 1300.90498)))
("SF_PLANTING" 0 ((4049.77376 7073.90622) (4015.83710 7057.76753) (3993.36075 7036.05079) (3983.16425 7012.73891)
(3989.44152 6998.49197)))
("SF_PLANTING" 0 ((4064.85713 7043.74084) (4057.30860 7032.43484) (4015.83710 7003.46018) (3989.44152 6998.49197)))
("SF_PLANTING" 0 ((3989.44152 3661.38722) (3998.18767 3687.78281) (4027.14932 3714.17839)))
("SF_MASONRY_AND_ARCH" 0 ((3996.98382 2473.60509) (3989.44152 2473.60509)))
("SF_PLANTING" 0 ((3989.44152 335.59672) (3989.44152 346.90894)))
("SF_PLANTING" 0 ((4030.92048 426.09446) (4015.99174 407.23982) (4022.17432 365.76833) (3989.44152 346.90894)))
("SF_PLANTING" 0 ((3989.44152 335.59672) (3996.83541 316.74208) (4004.52489 245.09898)))
("SF_PLANTING" 0 ((4008.29604 6481.90045) (4008.14106 6534.68450) (3996.98382 6546.00328)))
("SF_PLANTING" 0 ((3996.98382 3770.73948) (4008.51595 3733.25260) (4027.14932 3721.71946)))
("SF_PLANTING" 0 ((3996.98382 3770.73948) (4000.75373 3793.36391)))
("SF_PLANTING" 0 ((3996.98382 637.25396) (3996.98382 618.40215)))
("SF_PLANTING" 0 ((4042.23269 6851.43314) (4037.41176 6870.28631) (4018.55158 6907.98767) (4000.75373 6926.84740)))
("SF_PLANTING" 0 ((4211.91595 7055.05305) (4151.58371 7046.45532) (4079.93925 7008.74774) (4057.30860 6983.55679)
(4031.97002 6964.40701) (4000.75373 6926.84740)))
("SF_PLANTING" 0 ((4000.75373 6696.83258) (4012.06595 6693.06210)))
("SF_PLANTING" 0 ((4000.75373 6696.83258) (4008.29604 6753.39367)))
("SF_PLANTING" 0 ((4000.75373 3793.36391) (4019.60826 3793.36391)))
("SF_MASONRY_AND_ARCH" 0 ((4057.31482 1957.01357) (4019.60826 1956.86516) (4000.75373 1949.47183)))
("SF_PLANTING" 0 ((4053.54491 241.32636) (4015.83710 241.47477) (4004.52489 245.09898)))
("SF_PLANTING" 0 ((4015.83710 6787.33032) (4008.44389 6802.41301) (4008.29604 6832.57919)))
("SF_PLANTING" 0 ((4008.29604 6832.57919) (4023.37817 6833.78348) (4042.23269 6851.43314)))
("SF_PLANTING" 0 ((4015.83710 6787.33032) (4008.44389 6768.47636) (4008.29604 6753.39367)))
("SF_PLANTING" 0 ((4008.29604 6481.90045) (4177.97930 6481.89389) (4200.60328 6478.12964)))
("SF_PLANTING" 0 ((4128.95928 656.10860) (4008.29604 656.10860)))
("SF_PLANTING" 0 ((4019.60826 6583.71041) (4008.44389 6610.10532) (4008.44389 6636.49412) (4012.06595 6644.04197)))
("SF_ARCHITECTURE" 0 ((4012.06595 5735.29412) (4193.06143 5735.28756) (4211.91595 5731.52986) (4547.51131 5735.29412)
(4570.13575 5731.52986) (5026.39559 5735.29412)))
("SF_ARCHITECTURE" 0 ((4012.06595 5735.29412) (4006.77885 5716.44050) (4019.60826 5705.28303) (4166.66708 5705.12828)))
("SF_ARCHITECTURE" 0 ((4012.06595 5735.29412) (4013.11640 5757.91855) (4023.37817 5780.54299)))
("SF_PLANTING" 0 ((4015.83710 6787.33032) (4132.73043 6787.32376) (4155.35486 6783.55984) (4291.10147 6787.32376)
(4328.80803 6783.55984)))
("SF_PLANTING" 0 ((4049.77376 3940.42274) (4030.92048 3940.26776) (4019.60826 3932.88043)))
("SF_PLANTING" 0 ((4076.16934 3880.09050) (4067.42975 3849.92500) (4031.06833 3823.52941) (4019.60826 3793.36391)))
("SF_PLANTING" 0 ((4100.67873 3804.67613) (4072.39819 3804.52771) (4038.46154 3793.51176) (4019.60826 3793.36391)))
("SF_MASONRY_AND_ARCH" 0 ((4027.14932 2153.09174) (4019.60826 2153.09174)))
("SF_ARCHITECTURE" 0 ((4027.14932 5848.41629) (4008.45000 5818.25045) (4009.49333 5803.16742) (4023.37817 5780.54299)))
("SF_ARCHITECTURE" 0 ((6832.57919 5784.31380) (6798.64253 5780.54299) (6726.99876 5780.69106) (6708.14480 5784.31380)
(6421.56889 5784.30724) (6398.94446 5780.54299) (6236.80215 5780.54955) (6214.17771 5784.31380) (5788.08473 5784.30724)
(5765.45962 5780.54299) (5656.10860 5780.54955) (5633.48416 5784.31380) (5248.86878 5784.30724) (5226.24434 5780.54299)
(5120.66324 5780.54955) (5101.80995 5784.30724) (4758.67229 5784.30724) (4736.04785 5780.54299) (4438.16029 5788.08450)
(4419.30577 5780.54955) (4291.10147 5780.54955) (4253.39367 5788.08450) (4238.31029 5780.69106) (4181.74921 5780.54299)
(4162.89593 5788.08450) (4106.33484 5788.08450) (4087.48156 5780.69106) (4023.37817 5780.54299)))
("SF_ARCHITECTURE" 0 ((6825.03744 5844.64548) (6760.93541 5848.41629) (5610.85973 5848.40973) (5592.00645 5844.65860)
(5573.15192 5848.40973) (4027.14932 5848.41629)))
("SF_ARCHITECTURE" 0 ((4027.14932 5848.41629) (4008.45000 5871.04072) (4009.49989 5912.51222) (4015.84333 5918.85600)
(4049.77376 5923.83100)))
("SF_PLANTING" 0 ((4027.14932 3714.17839) (4027.14932 3721.71946)))
("SF_PLANTING" 0 ((4100.67873 3804.67613) (4087.33314 3778.28054) (4053.55113 3755.50803) (4027.14932 3721.71946)))
("SF_PLANTING" 0 ((4038.46154 3585.97285) (4038.30690 3702.86550) (4027.14932 3714.17839)))
("SF_ARCHITECTURE" 0 ((4030.92048 5629.71335) (4087.47466 5629.86143) (4095.02262 5633.48416)))
("SF_PLANTING" 0 ((4030.92048 1236.80147) (4294.87138 1244.34389)))
("SF_PLANTING" 0 ((4030.92048 426.09446) (4032.80543 461.91459)))
("SF_PLANTING" 0 ((4030.92048 426.09446) (4049.76753 427.29785) (4057.31482 441.17647)))
("SF_PLANTING" 0 ((4032.80543 461.91459) (4049.62568 452.34095) (4057.31482 441.17647)))
("SF_PLANTING" 0 ((4032.80543 461.91459) (4038.46154 505.27998)))
("SF_MASONRY_AND_ARCH" 0 ((4034.69038 1338.61143) (4064.85713 1334.84853) (4079.93925 1338.46437) (4170.43699
1338.61833) (4196.83258 1342.38405)))
("SF_PLANTING" 0 ((4038.46154 3883.86165) (4076.16934 3880.09050)))
("SF_PLANTING" 0 ((4038.46154 3585.97285) (4038.61618 3250.38371) (4042.38665 3243.89219) (4057.31482 3239.06459)))
("SF_MASONRY_AND_ARCH" 0 ((4038.46154 2620.66391) (4064.85713 2616.89265) (4087.48156 2620.65769) (4226.99808
2620.81165) (4242.08145 2624.42817) (4268.47704 2620.67014) (4309.95475 2624.43439) (4407.84570 2621.86799) (4419.30577
2631.97613)))
("SF_MASONRY_AND_ARCH" 0 ((4038.46154 2518.85396) (4223.22817 2522.77217) (4238.31029 2526.38869) (4279.78925
2523.82240) (4366.51584 2526.54265) (4415.53586 2533.93665)))
("SF_PLANTING" 0 ((4121.41821 6847.66188) (4083.71041 6840.26878) (4042.23269 6851.43314)))
("SF_MASONRY_AND_ARCH" 0 ((4042.23269 2714.93213) (4068.62704 2722.47387)))
("SF_MASONRY_AND_ARCH" 0 ((4042.23269 1813.72455) (4049.77376 1813.72455)))
("SF_PLANTING" 0 ((4049.77376 7073.90622) (4064.85713 7043.74084)))
("SF_PLANTING" 0 ((4049.77376 7073.90622) (4068.62704 7087.79853) (4083.70419 7092.45747) (4090.04106 7088.83462)
(4082.65373 7055.05962) (4064.85713 7043.74084)))
("SF_ARCHITECTURE" 0 ((6798.64253 5923.83100) (6787.33032 5920.06697) (5901.20690 5920.05385) (5878.58247 5916.28959)
(5644.79638 5916.29615) (5622.17195 5920.06041) (5237.55656 5920.05385) (5214.93213 5916.28959) (5169.68326 5920.05385)
(5124.43439 5916.28959) (5071.64446 5916.43767) (5056.56109 5920.05385) (4992.45894 5916.28959) (4883.10667 5916.29615)
(4864.25339 5920.05385) (4720.96572 5920.05385) (4698.34129 5916.28959) (4671.94570 5920.05385) (4106.33484 5920.05385)
(4064.85713 5916.29615) (4049.77376 5923.83100)))
("SF_ARCHITECTURE" 0 ((4200.60328 6044.49480) (4196.67794 6025.78903) (4064.86335 5945.39932) (4049.77376 5923.83100)))
("SF_MASONRY_AND_ARCH" 0 ((4053.54491 1779.78790) (4049.77376 1813.72455)))
("SF_MASONRY_AND_ARCH" 0 ((4117.64706 1821.26697) (4102.56369 1828.65407) (4064.85713 1828.65407) (4057.32172
1824.88281) (4049.77376 1813.72455)))
("SF_PLANTING" 0 ((4095.02262 595.77771) (4064.85713 588.08066) (4050.97828 573.15328) (4049.77376 554.29864)))
("SF_PLANTING" 0 ((4053.54491 4023.37817) (4061.92862 4026.63258) (4091.39989 3993.36075) (4128.95928 3963.04717)))
("SF_PLANTING" 0 ((4053.54491 241.32636) (4061.09219 234.98394) (4079.93925 230.16256) (4121.41821 233.78676)
(4162.89593 230.16256) (4174.20814 234.84242) (4189.29152 248.86878)))
("SF_PLANTING" 0 ((4053.54491 241.32636) (4058.51301 260.18100) (4076.16867 274.20735) (4087.48156 275.26301)))
("SF_MASONRY_AND_ARCH" 0 ((4057.31482 3239.06459) (4057.31482 2956.25916)))
("SF_PLANTING" 0 ((4057.31482 3239.06459) (4083.71041 3242.83586) (4106.33484 3239.06459)))
("SF_MASONRY_AND_ARCH" 0 ((4057.31482 2956.25916) (4083.71041 2952.48869) (4106.33484 2956.25916)))
("SF_MASONRY_AND_ARCH" 0 ((4057.31482 2956.25916) (4046.00950 2955.05509) (4039.66606 2948.71131) (4039.66606
2907.23982) (4053.54491 2893.36120) (4068.47919 2890.95294) (4090.05419 2861.99095) (4116.59038 2801.65939) (4125.04027
2763.95147) (4126.24480 2722.47387) (4132.87828 2711.31629) (4144.04265 2707.39729) (4260.93473 2711.30939) (4276.01810
2714.92590) (4325.03812 2714.78439) (4340.12025 2711.16787) (4675.71686 2711.16787) (4698.34129 2714.93213) (4724.73563
2711.16787) (5226.24434 2711.16787) (5245.09762 2714.92590) (5452.48869 2717.50475) (5603.31867 2714.92590) (5622.17195
2711.16787) (6568.62771 2711.15543) (6587.48088 2707.39661) (6674.20124 2707.54502) (6681.59525 2714.93903) (6690.48880
2801.65939) (6706.95373 2828.05430) (6716.74287 2854.44921) (6745.85192 2892.15713)))
("SF_MASONRY_AND_ARCH" 0 ((4057.31482 1957.01357) (4064.85713 1945.70136)))
("SF_MASONRY_AND_ARCH" 0 ((4057.31482 1957.01357) (4072.39819 1964.40679) (4204.37364 1964.70305) (4234.54038
1972.09627)))
("SF_PLANTING" 0 ((4098.79378 460.03111) (4057.31482 441.17647)))
("SF_PLANTING" 0 ((4121.41821 369.53337) (4106.33484 383.41742) (4083.71041 390.05679) (4064.85713 384.61538)))
("SF_PLANTING" 0 ((4226.99808 6734.53971) (4151.58371 6734.39186) (4132.73043 6730.76923) (4068.62704 6734.53971)))
("SF_PLANTING" 0 ((4072.39819 3936.65158) (4092.08722 3946.54559) (4121.41821 3940.42274)))
("SF_MASONRY_AND_ARCH" 0 ((4087.48156 980.39310) (4079.93925 972.85068) (4072.39819 972.85068)))
("SF_PLANTING" 0 ((4121.41821 3925.33937) (4076.16934 3880.09050)))
("SF_MASONRY_AND_ARCH" 0 ((4076.16934 1742.08145) (4098.79378 1745.70419) (4226.99808 1748.42523) (4294.87138
1745.85124)))
("SF_MASONRY_AND_ARCH" 0 ((4151.58371 1470.58824) (4083.71041 1470.58824)))
("SF_MASONRY_AND_ARCH" 0 ((4087.48156 1655.35351) (4102.55747 1657.92127) (4110.10600 1647.81391)))
("SF_MASONRY_AND_ARCH" 0 ((4087.48156 1598.79242) (4140.27149 1595.02885) (4204.37364 1595.17036) (4226.99808
1598.79242) (4294.87138 1595.02262)))
("SF_MASONRY_AND_ARCH" 0 ((4087.48156 1598.79242) (4088.68541 1621.41686) (4110.10600 1647.81391)))
("SF_MASONRY_AND_ARCH" 0 ((4087.48156 1425.33937) (4102.56369 1429.10916) (4196.83258 1425.33937)))
("SF_PLANTING" 0 ((4087.48156 275.26301) (4087.63552 297.88744) (4091.40645 305.27523) (4113.87590 309.19966)))
("SF_PLANTING" 0 ((4113.87590 279.03563) (4087.48156 275.26301)))
("SF_PLANTING" 0 ((4136.50034 4049.77376) (4117.64706 4060.93133) (4091.25147 4061.08597)))
("SF_PLANTING" 0 ((4091.25147 3831.07048) (4102.56369 3815.98835)))
("SF_MASONRY_AND_ARCH" 0 ((4095.02262 2198.34061) (4147.81256 2194.86629) (4162.89593 2198.33439) (4245.85260
2198.34061)))
("SF_MASONRY_AND_ARCH" 0 ((4095.02262 2198.34061) (4098.79378 2220.96505)))
("SF_PLANTING" 0 ((4095.02262 358.22115) (4106.33484 355.66097) (4121.41821 369.53337)))
("SF_MASONRY_AND_ARCH" 0 ((6745.85192 2892.15713) (6738.30407 2902.27138) (6719.45701 2907.23360) (6523.37885
2903.46934) (6496.98314 2907.23982) (4098.79378 2907.23982)))
("SF_PLANTING" 0 ((4098.79378 460.03111) (4117.64706 448.71889)))
("SF_PLANTING" 0 ((4098.79378 460.03111) (4102.56369 471.34333)))
("SF_PLANTING" 0 ((4200.60373 3800.90498) (4117.64706 3797.28224) (4100.67873 3804.67613)))
("SF_PLANTING" 0 ((4100.67873 3804.67613) (4102.56369 3815.98835)))
("SF_PLANTING" 0 ((4102.56369 4038.46154) (4099.99762 4034.54253) (4102.72523 4028.19910) (4132.73043 4015.83710)))
("SF_PLANTING" 0 ((4166.66708 3880.09050) (4160.18145 3868.77828) (4154.99242 3842.75170) (4132.73043 3837.70419)
(4102.56369 3815.98835)))
("SF_PLANTING" 0 ((4136.50034 3239.06459) (4106.33484 3239.06459)))
("SF_MASONRY_AND_ARCH" 0 ((4106.33484 3239.06459) (4106.33484 2956.25916)))
("SF_MASONRY_AND_ARCH" 0 ((4136.50034 2956.25916) (4106.33484 2956.25916)))
("SF_PLANTING" 0 ((4106.33484 595.77771) (4113.87590 595.77771)))
("SF_PLANTING" 0 ((4132.73043 3729.26052) (4110.10600 3725.49061)))
("SF_MASONRY_AND_ARCH" 0 ((4121.41821 1930.61867) (4110.10600 1930.61867)))
("SF_MASONRY_AND_ARCH" 0 ((4110.10600 1647.81391) (4117.64706 1647.81391)))
("SF_PLANTING" 0 ((4121.41821 3880.09050) (4113.87590 3876.31934)))
("SF_PLANTING" 0 ((4113.87590 279.03563) (4113.87590 309.19966)))
("SF_PLANTING" 0 ((4113.87590 309.19966) (4147.81256 312.97229)))
("SF_PLANTING" 0 ((4113.87590 279.03563) (4125.18880 272.69808) (4139.22172 279.18891) (4147.65860 294.11765)
(4147.81256 312.97229)))
("SF_PLANTING" 0 ((4140.27149 6994.72070) (4121.72070 6983.26753) (4121.41821 6975.86753)))
("SF_PLANTING" 0 ((4196.83258 6843.89140) (4189.28462 6840.26878) (4159.12477 6840.26878) (4121.41821 6847.66188)))
("SF_PLANTING" 0 ((4121.41821 6847.66188) (4109.95758 6874.05724) (4057.32172 6911.91301) (4047.35577 6930.47036)
(4064.85713 6938.00520) (4110.10600 6925.64989) (4151.58371 6907.99423)))
("SF_PLANTING" 0 ((4121.41821 3925.33937) (4121.41821 3940.42274)))
("SF_PLANTING" 0 ((4121.41821 3940.42274) (4128.95928 3963.04717)))
("SF_PLANTING" 0 ((4121.41821 3925.33937) (4147.80633 3920.36437) (4155.35486 3910.25600)))
("SF_MASONRY_AND_ARCH" 0 ((4121.41821 1885.36980) (4121.41821 1862.74536)))
("SF_PLANTING" 0 ((4121.41821 369.53337) (4128.95928 369.53337)))
("SF_PLANTING" 0 ((4166.66708 3966.81708) (4159.11855 3963.19502) (4128.95928 3963.04717)))
("SF_PLANTING" 0 ((4128.95928 377.07296) (4128.95928 369.53337)))
("SF_PLANTING" 0 ((4147.81256 414.78224) (4130.16380 395.92138) (4128.95928 377.07296)))
("SF_PLANTING" 0 ((4166.66708 388.38518) (4128.95928 377.07296)))
("SF_PLANTING" 0 ((4147.81256 320.51188) (4137.70509 335.59672) (4128.95928 369.53337)))
("SF_PLANTING" 0 ((4132.73043 6945.70136) (4136.50034 6953.24310)))
("SF_PLANTING" 0 ((4136.50034 558.06844) (4132.73043 565.61086)))
("SF_PLANTING" 0 ((4155.35486 3910.25600) (4140.42613 3901.67138) (4136.50034 3895.17387)))
("SF_PLANTING" 0 ((4177.97930 3239.06459) (4136.50034 3239.06459)))
("SF_MASONRY_AND_ARCH" 0 ((4136.50034 3239.06459) (4140.11686 3197.58699) (4136.50724 3178.73303) (4136.50034
2956.25916)))
("SF_MASONRY_AND_ARCH" 0 ((4177.97930 2956.25916) (4136.50034 2956.25916)))
("SF_PLANTING" 0 ((4151.58371 897.43495) (4136.50034 859.72851)))
("SF_PLANTING" 0 ((4155.35486 1074.66063) (4147.81256 1070.89084) (4140.27149 1078.43043)))
("SF_PLANTING" 0 ((4144.04265 4091.25147) (4151.58993 4084.90147) (4168.55204 4079.93925)))
("SF_SOLAR" 0 ((4147.81256 8193.81606) (4155.35486 8205.12828)))
("SF_PLANTING" 0 ((4151.58371 1123.67930) (4147.81256 1112.36708)))
("SF_PLANTING" 0 ((4166.66708 388.38518) (4165.46233 399.69740) (4147.81256 414.78224)))
("SF_PLANTING" 0 ((4196.83258 437.40667) (4155.36109 438.29389) (4149.01731 433.48699) (4147.81256 414.78224)))
("SF_PLANTING" 0 ((4147.81256 320.51188) (4166.66708 320.51188)))
("SF_PLANTING" 0 ((4147.81256 320.51188) (4147.81256 312.97229)))
("SF_PLANTING" 0 ((4159.12477 6889.14027) (4152.78133 6896.68857) (4151.58371 6907.99423)))
("SF_PLANTING" 0 ((4177.97930 6919.30645) (4159.13167 6918.10215) (4151.58371 6907.99423)))
("SF_MASONRY_AND_ARCH" 0 ((4151.58371 2869.53269) (4177.97930 2861.99095) (4430.61799 2861.99717) (4453.24242
2869.53247) (4766.21459 2869.53247) (4788.83903 2861.99095) (5018.85328 2861.99717) (5037.70781 2869.53247) (6549.77376
2865.75520) (6564.85645 2862.13869) (6640.27149 2861.99095) (6662.89593 2865.76143)))
("SF_PLANTING" 0 ((4151.58371 897.43495) (4185.52036 897.43495)))
("SF_PLANTING" 0 ((4151.58371 897.43495) (4151.73835 916.28959) (4155.50882 923.82443) (4170.43699 934.08710)
(4185.52036 935.14423)))
("SF_PLANTING" 0 ((4211.91595 3857.46606) (4204.52206 3872.54943) (4200.23473 3906.11708) (4155.35486 3910.25600)))
("SF_SOLAR" 0 ((4381.59921 7850.67873) (4367.71346 7873.30317) (4354.15385 7914.78133) (4167.87093 8190.04525)
(4166.51867 8208.89898) (4159.12477 8227.75271)))
("SF_PLANTING" 0 ((4162.89593 603.31731) (4166.66708 610.85973)))
("SF_ARCHITECTURE" 0 ((4170.43699 5656.10860) (4166.66708 5705.12828)))
("SF_ARCHITECTURE" 0 ((4166.66708 5705.12828) (4219.45701 5705.27647) (4234.54038 5708.89231) (4313.72590 5708.89231)
(4336.35034 5705.12828) (4611.61346 5705.13484) (4634.23790 5708.89887) (4811.46346 5705.13484) (4856.71233 5708.89231)
(4898.19005 5705.12828) (4920.81448 5708.89231) (5026.39559 5708.89887)))
("SF_PLANTING" 0 ((4166.66708 3966.81708) (4208.14480 3966.81708)))
("SF_PLANTING" 0 ((4170.43699 4004.52489) (4166.81493 3996.97692) (4166.66708 3966.81708)))
("SF_PLANTING" 0 ((4170.43699 663.65102) (4166.66708 652.33880)))
("SF_PLANTING" 0 ((4166.66708 388.38518) (4181.74921 343.13631)))
("SF_PLANTING" 0 ((4166.66708 320.51188) (4192.00532 294.11765) (4201.65984 271.49321) (4215.68586 252.63857)))
("SF_PLANTING" 0 ((4166.66708 320.51188) (4181.74921 343.13631)))
("SF_PLANTING" 0 ((4168.55204 4079.93925) (4200.60373 4071.20679) (4215.68586 4062.14265) (4242.08145 4061.08597)))
("SF_PLANTING" 0 ((4170.43699 4004.52489) (4166.67330 4015.83710) (4168.55204 4079.93925)))
("SF_PLANTING" 0 ((4174.20814 4113.87590) (4168.55204 4079.93925)))
("SF_ARCHITECTURE" 0 ((4170.43699 5595.77636) (4159.13167 5633.48416) (4160.32296 5644.79638) (4170.43699 5656.10860)))
("SF_ARCHITECTURE" 0 ((6662.89593 5659.87941) (4313.72590 5659.87941) (4291.10147 5656.11516) (4170.43699 5656.10860)))
("SF_ARCHITECTURE" 0 ((4170.43699 5595.77636) (4141.47602 5569.38133) (4140.42613 5550.52749) (4151.58371 5536.64921)
(4177.97930 5531.67421)))
("SF_ARCHITECTURE" 0 ((4170.43699 5595.77636) (4219.45701 5595.92477) (4234.54038 5599.54129) (4645.55011 5599.54751)))
("SF_PLANTING" 0 ((4170.43699 4004.52489) (4193.05520 3993.20645) (4208.14480 3966.81708)))
("SF_PLANTING" 0 ((4170.43699 3710.40724) (4170.65792 3722.55520) (4195.63495 3766.96833) (4200.60373 3800.90498)))
("SF_PLANTING" 0 ((4189.29152 248.86878) (4170.43699 267.72342)))
("SF_SOLAR" 0 ((4181.74921 8208.89898) (4174.20814 8208.89898)))
("SF_PLANTING" 0 ((4177.97930 6919.30645) (4174.20814 6900.45249)))
("SF_PLANTING" 0 ((4174.20814 4193.06143) (4193.06833 4160.18145) (4223.22817 4147.96097) (4245.85260 4147.81256)))
("SF_PLANTING" 0 ((4174.20814 4113.87590) (4169.23314 4132.58201) (4147.81256 4144.19661) (4118.83846 4181.74921)
(4114.03088 4204.36742) (4121.42443 4211.61256) (4136.50034 4206.94717) (4147.81256 4198.03676) (4174.20814
4193.06143)))
("SF_ARCHITECTURE" 0 ((4174.20814 4193.06143) (4174.21437 4660.63348) (4177.97930 4683.25792) (4177.97240 5000.00000)
(4174.21437 5018.85328) (4174.21437 5128.20554) (4177.97240 5147.05882) (4177.97930 5531.67421)))
("SF_PLANTING" 0 ((4174.20814 4113.87590) (4219.45701 4092.30814) (4238.31029 4091.25147)))
("SF_SOLAR" 0 ((4177.97930 8201.35747) (4181.74921 8208.89898)))
("SF_PLANTING" 0 ((4211.91595 7055.05305) (4203.31821 7028.65735) (4177.97930 6998.49197)))
("SF_PLANTING" 0 ((4177.97930 6919.30645) (4200.60373 6940.87410) (4238.31029 6945.54649) (4253.39367 6938.15962)))
("SF_ARCHITECTURE" 0 ((4249.62251 5527.90305) (4230.76923 5535.29695) (4189.29152 5535.29695) (4177.97930 5531.67421)))
("SF_PLANTING" 0 ((4177.97930 3239.06459) (4211.91595 3239.06459)))
("SF_MASONRY_AND_ARCH" 0 ((4177.97930 3239.06459) (4177.97930 2956.25916)))
("SF_MASONRY_AND_ARCH" 0 ((4177.97930 2956.25916) (4211.91595 2956.25916)))
("SF_SOLAR" 0 ((4181.74921 8208.89898) (4969.83450 8208.89898) (4984.91663 8208.89898) (5000.00000 8208.89898)
(5750.37749 8208.89898) (5779.48631 8182.50385) (5804.22376 8137.25498) (5984.16290 7892.15690)))
("SF_PLANTING" 0 ((4181.74921 343.13631) (4234.54038 335.59672)))
("SF_PLANTING" 0 ((4185.52036 1010.55713) (4193.06143 1010.55713)))
("SF_PLANTING" 0 ((4219.45701 852.18609) (4193.21640 867.27579) (4185.52036 897.43495)))
("SF_PLANTING" 0 ((4255.27862 912.51980) (4234.54038 905.13201) (4204.37364 904.82896) (4185.52036 897.43495)))
("SF_PLANTING" 0 ((4189.29152 248.86878) (4215.68586 252.63857)))
("SF_PLANTING" 0 ((4193.06143 1010.55713) (4204.38054 996.53145) (4219.45701 991.70532)))
("SF_PLANTING" 0 ((4253.39367 1029.41176) (4223.22817 1032.12590) (4204.37432 1024.44333) (4193.06143 1010.55713)))
("SF_PLANTING" 0 ((4196.83258 6843.89140) (4253.39367 6843.89140)))
("SF_PLANTING" 0 ((4196.83258 6843.89140) (4198.03710 6877.67975) (4219.45701 6886.57410) (4238.31719 6906.78993)
(4253.39367 6906.79649) (4283.55294 6887.62342) (4291.10147 6889.14027)))
("SF_PLANTING" 0 ((4245.85260 3985.67161) (4244.79593 4000.75373) (4238.16244 4011.91810) (4211.91595 4024.57636)
(4196.83258 4038.46154)))
("SF_MASONRY_AND_ARCH" 0 ((4223.22817 2658.37104) (4196.83258 2658.37104)))
("SF_MASONRY_AND_ARCH" 0 ((4196.83258 1425.33937) (4201.80102 1406.64005) (4215.68586 1400.00079) (4234.54038
1402.70249) (4283.55916 1398.95000) (4294.87138 1402.71493)))
("SF_MASONRY_AND_ARCH" 0 ((4196.83258 1425.33937) (4200.60373 1436.65158)))
("SF_MASONRY_AND_ARCH" 0 ((4215.68586 1327.29921) (4196.83258 1342.38405)))
("SF_MASONRY_AND_ARCH" 0 ((4200.60373 1365.00848) (4196.83258 1342.38405)))
("SF_PLANTING" 0 ((4196.83258 437.40667) (4205.43032 414.78224) (4215.68654 403.77172) (4234.54038 403.47002)))
("SF_PLANTING" 0 ((4279.78925 471.34333) (4264.70588 474.96538) (4238.31029 474.05679) (4208.14480 452.34095)
(4196.83258 437.40667)))
("SF_PLANTING" 0 ((4200.60328 6478.12964) (4200.60328 6063.34842) (4200.60328 6044.49480)))
("SF_PLANTING" 0 ((4276.01810 6561.08597) (4275.86346 6489.44197) (4272.09299 6485.67783) (4260.93473 6478.28428)
(4200.60328 6478.12964)))
("SF_ARCHITECTURE" 0 ((6632.72975 6048.26538) (6595.02262 6048.11719) (6568.62771 6040.73710) (6474.35871 6048.26550)
(6236.80215 6048.26550) (6214.17771 6048.26550) (4309.95475 6052.02964) (4249.62251 6044.64299) (4200.60328
6044.49480)))
("SF_PLANTING" 0 ((4200.60373 3800.90498) (4208.14480 3804.67613)))
("SF_MASONRY_AND_ARCH" 0 ((4200.60373 1478.13066) (4204.52862 1468.02183) (4230.76923 1466.81844)))
("SF_SOLAR" 0 ((4204.37364 8163.65011) (4211.91595 8163.65011)))
("SF_MASONRY_AND_ARCH" 0 ((4204.37364 2322.77500) (4219.45701 2319.01075) (4389.14027 2315.23382) (4404.22364
2315.23382) (4457.01357 2315.23382)))
("SF_MASONRY_AND_ARCH" 0 ((4204.37364 2322.77500) (4208.14480 2371.79514)))
("SF_PLANTING" 0 ((4226.99808 3966.81708) (4208.14480 3966.81708)))
("SF_PLANTING" 0 ((4253.39367 3804.67613) (4208.14480 3804.67613)))
("SF_PLANTING" 0 ((4208.14480 3804.67613) (4211.91595 3857.46606)))
("SF_PLANTING" 0 ((4211.91595 7055.05305) (4226.99808 7066.36527)))
("SF_PLANTING" 0 ((4211.91595 3857.46606) (4226.99186 3865.15554) (4243.13744 3891.39649) (4253.39367 3898.94378)))
("SF_PLANTING" 0 ((4211.91595 3699.09502) (4219.61165 3721.71946) (4272.24695 3778.28054)))
("SF_PLANTING" 0 ((4245.85260 3235.29412) (4238.30407 3238.91686) (4211.91595 3239.06459)))
("SF_MASONRY_AND_ARCH" 0 ((4211.91595 3239.06459) (4211.91595 2956.25916)))
("SF_MASONRY_AND_ARCH" 0 ((4211.91595 2956.25916) (4242.08145 2960.03043)))
("SF_PLANTING" 0 ((4215.68586 1327.29921) (4212.06380 1319.75204) (4211.91595 1293.36256)))
("SF_PLANTING" 0 ((4211.91595 938.91403) (4212.97138 953.99118) (4219.45701 961.53846)))
("SF_SOLAR" 0 ((4392.91143 7933.63495) (4344.94118 7990.19615) (4215.68586 8178.73303)))
("SF_MASONRY_AND_ARCH" 0 ((4215.68586 2466.06335) (4211.92217 2420.81448) (4215.84084 2410.70645) (4449.47183
2409.34762) (4459.72805 2401.95430) (4467.12127 2386.87783) (4460.78473 2371.79514)))
("SF_MASONRY_AND_ARCH" 0 ((4215.68586 1825.03744) (4230.76923 1828.66097) (4294.87138 1828.80871)))
("SF_MASONRY_AND_ARCH" 0 ((4215.68586 1327.29921) (4223.23439 1330.92342) (4283.55916 1331.21889) (4294.87138
1334.84163)))
("SF_PLANTING" 0 ((4215.68586 252.63857) (4230.76923 252.63857)))
("SF_PLANTING" 0 ((4219.45701 991.70532) (4219.45701 961.53846)))
("SF_PLANTING" 0 ((4268.47704 991.70532) (4238.31029 995.17896) (4219.45701 991.70532)))
("SF_PLANTING" 0 ((4226.99808 961.53846) (4219.45701 961.53846)))
("SF_PLANTING" 0 ((4219.45701 852.18609) (4219.61165 607.09480) (4223.38213 600.75238) (4238.31029 599.54751)))
("SF_PLANTING" 0 ((6591.25215 852.18609) (4619.15577 852.19299) (4604.07240 855.66176) (4592.76018 852.33450)
(4521.11572 852.19299) (4498.49129 855.95871) (4415.53586 855.95181) (4392.91143 852.18609) (4234.54038 855.95181)
(4219.45701 852.18609)))
("SF_MASONRY_AND_ARCH" 0 ((4223.22817 1700.60238) (4223.22817 1685.52036)))
("SF_PLANTING" 0 ((4223.22817 1112.36708) (4253.39367 1115.99129) (4306.18360 1103.62885) (4325.03812 1090.93371)
(4351.43247 1085.97285)))
("SF_SOLAR" 0 ((4234.54038 8137.25498) (4226.99808 8125.94276)))
("SF_PLANTING" 0 ((4226.99808 3966.81708) (4228.20283 3959.26980) (4249.46855 3936.65158) (4253.39367 3925.33937)))
("SF_PLANTING" 0 ((4245.85260 3985.67161) (4234.54661 3978.12308) (4226.99808 3966.81708)))
("SF_MASONRY_AND_ARCH" 0 ((4298.64253 1655.35351) (4287.33032 1658.97771) (4226.99808 1659.12613)))
("SF_MASONRY_AND_ARCH" 0 ((4230.76923 2111.61414) (4291.09457 2111.76188) (4298.64253 2115.38462)))
("SF_PLANTING" 0 ((4296.75758 243.21267) (4279.78925 233.94005) (4253.39367 233.94005) (4230.76923 252.63857)))
("SF_PLANTING" 0 ((4238.31029 263.95079) (4230.76923 252.63857)))
("SF_MASONRY_AND_ARCH" 0 ((4234.54038 2024.88688) (4234.54038 1972.09627)))
("SF_MASONRY_AND_ARCH" 0 ((4238.31029 2066.36527) (4234.68824 2058.81663) (4234.54038 2024.88688)))
("SF_MASONRY_AND_ARCH" 0 ((4294.87138 2028.65735) (4234.54038 2024.88688)))
("SF_MASONRY_AND_ARCH" 0 ((4294.87138 1972.09627) (4234.54038 1972.09627)))
("SF_PLANTING" 0 ((4234.54038 429.86425) (4234.54038 403.47002)))
("SF_PLANTING" 0 ((4264.70588 388.38518) (4249.62251 389.59005) (4234.54038 403.47002)))
("SF_PLANTING" 0 ((4234.54038 335.59672) (4245.85260 316.74208)))
("SF_PLANTING" 0 ((4234.54038 335.59672) (4242.08145 365.76075)))
("SF_SOLAR" 0 ((4238.31029 8163.65011) (4453.24242 8163.65011)))
("SF_PLANTING" 0 ((4238.31029 4091.25147) (4242.08145 4061.08597)))
("SF_PLANTING" 0 ((4249.62251 4125.18812) (4239.36697 4113.87590) (4238.31029 4091.25147)))
("SF_PLANTING" 0 ((4238.31029 599.54751) (4239.51505 573.15814) (4253.39367 565.61776) (6233.03167 565.61708)
(6248.11437 569.23360) (6365.00781 569.38756) (6391.40271 573.15328) (6417.79762 565.61086)))
("SF_PLANTING" 0 ((4238.31029 599.54751) (4283.55916 603.31731) (6595.02262 603.31731) (6628.95928 595.77771)))
("SF_PLANTING" 0 ((4238.31029 263.95079) (4245.85260 316.74208)))
("SF_PLANTING" 0 ((4238.31029 263.95079) (4268.47704 271.49321)))
("SF_PLANTING" 0 ((4242.08145 4061.08597) (4272.39536 4027.29740) (4298.64253 4015.83710)))
("SF_MASONRY_AND_ARCH" 0 ((4268.47704 2960.03043) (4242.08145 2960.03043)))
("SF_MASONRY_AND_ARCH" 0 ((4245.85260 3235.29412) (4242.08145 2960.03043)))
("SF_PLANTING" 0 ((4245.85260 6870.28631) (4253.39367 6843.89140)))
("SF_PLANTING" 0 ((4268.47704 4260.93473) (4245.85260 4260.93473)))
("SF_PLANTING" 0 ((4245.85260 4260.93473) (4242.08145 4249.62251) (4242.08767 4177.97930) (4245.85260 4147.81256)))
("SF_ARCHITECTURE" 0 ((4249.62251 5527.90305) (4249.61629 5267.72206) (4245.85882 5248.86878) (4249.62251 5018.85328)
(4245.85882 4996.22885) (4245.85260 4260.93473)))
("SF_PLANTING" 0 ((4249.62251 4125.18812) (4245.85260 4147.81256)))
("SF_PLANTING" 0 ((4245.85260 3985.67161) (4268.47704 3971.64491) (4309.95475 3963.04717)))
("SF_PLANTING" 0 ((4245.85260 3235.29412) (4302.41369 3239.06459)))
("SF_MASONRY_AND_ARCH" 0 ((4298.64253 2198.34061) (4279.78925 2194.57014) (4245.85260 2198.34061)))
("SF_MASONRY_AND_ARCH" 0 ((4298.64253 2224.73631) (4272.24695 2228.49367) (4253.39989 2226.25939) (4246.00656
2217.19457) (4245.85260 2198.34061)))
("SF_PLANTING" 0 ((4272.24695 316.74208) (4245.85260 316.74208)))
("SF_ARCHITECTURE" 0 ((4249.62251 6440.42229) (4279.78925 6432.88077) (4313.72590 6433.03541) (4336.35034 6440.42229)
(6530.91980 6440.42240) (6553.54423 6436.65158)))
("SF_ARCHITECTURE" 0 ((4325.03812 5527.90305) (4291.10147 5539.21527) (4268.47704 5538.15916) (4249.62251 5527.90305)))
("SF_PLANTING" 0 ((4249.62251 4125.18812) (4263.64921 4113.72805) (4280.83880 4080.08767) (4298.64253 4072.39819)))
("SF_MASONRY_AND_ARCH" 0 ((4294.87138 1466.81844) (4249.62251 1466.81844)))
("SF_PLANTING" 0 ((4349.54751 1012.44344) (4336.35283 1024.43993) (4294.87206 1037.10747) (4284.76391 1048.26640)
(4279.63428 1066.97115) (4264.70588 1077.23326) (4249.62251 1074.66063)))
("SF_SOLAR" 0 ((4253.39367 8141.02557) (4441.93020 8141.03213) (4457.01357 8144.79638)))
("SF_PLANTING" 0 ((4419.30577 6836.34966) (4377.82805 6843.74310) (4294.87138 6840.12093) (4253.39367 6843.89140)))
("SF_PLANTING" 0 ((4347.66256 3883.86165) (4343.73676 3890.35294) (4313.72590 3900.13541) (4279.78925 3920.51278)
(4253.39367 3925.33937)))
("SF_PLANTING" 0 ((4253.39367 3925.33937) (4253.39367 3898.94378)))
("SF_PLANTING" 0 ((4253.39367 3898.94378) (4289.89672 3865.00713) (4294.87138 3831.07048)))
("SF_PLANTING" 0 ((4253.39367 3804.67613) (4272.24695 3778.28054)))
("SF_PLANTING" 0 ((4279.78925 3827.30057) (4253.39367 3804.67613)))
("SF_PLANTING" 0 ((4255.27862 912.51980) (4272.24695 901.35532) (4340.12025 901.35532) (4351.43247 906.03371)
(4366.51584 920.05939)))
("SF_PLANTING" 0 ((4260.93473 920.05939) (4253.39367 916.28959) (4255.27862 912.51980)))
("SF_PLANTING" 0 ((4260.93473 920.05939) (4255.27862 912.51980)))
("SF_PLANTING" 0 ((4279.78925 3827.30057) (4257.16482 3857.46606)))
("SF_MASONRY_AND_ARCH" 0 ((4260.93473 2662.14152) (4370.28699 2662.14152)))
("SF_PLANTING" 0 ((4260.93473 920.05939) (4260.93473 935.14423)))
("SF_PLANTING" 0 ((4268.47704 961.53846) (4262.13258 953.99118) (4260.93473 935.14423)))
("SF_PLANTING" 0 ((4300.52749 959.65215) (4287.32410 936.34762) (4260.93473 935.14423)))
("SF_MASONRY_AND_ARCH" 0 ((4268.47704 3212.66968) (4265.00238 3201.35747) (4268.47014 3174.96256) (4264.70588
3152.33812) (4268.47704 2960.03043)))
("SF_MASONRY_AND_ARCH" 0 ((4268.47704 2960.03043) (4283.55916 2956.25916) (4298.64253 2960.03043)))
("SF_PLANTING" 0 ((4268.47704 991.70532) (4268.47704 961.53846)))
("SF_PLANTING" 0 ((4268.47704 991.70532) (4287.33032 995.32670) (4302.41369 987.93269)))
("SF_PLANTING" 0 ((4268.47704 961.53846) (4300.52749 959.65215)))
("SF_PLANTING" 0 ((4296.75758 243.21267) (4268.47704 271.49321)))
("SF_PLANTING" 0 ((4272.24695 316.74208) (4272.09910 279.04050) (4268.47704 271.49321)))
("SF_PLANTING" 0 ((4340.12025 3774.50939) (4272.24695 3778.28054)))
("SF_PLANTING" 0 ((4272.24695 316.74208) (4287.17568 324.43778) (4302.41369 354.44853)))
("SF_PLANTING" 0 ((4276.01810 6561.08597) (4276.16618 6700.60305) (4283.71414 6723.22093) (4309.95475 6735.73744)
(4323.83993 6749.62319) (4328.80803 6783.55984)))
("SF_PLANTING" 0 ((4276.01810 6561.08597) (4400.45249 6561.09253) (4426.84762 6564.85645)))
("SF_SOLAR" 0 ((4279.78925 8107.08891) (4306.18360 8099.84367) (4328.80803 8103.31833)))
("SF_PLANTING" 0 ((4279.78925 3827.30057) (4291.10147 3827.30057) (4294.87138 3831.07048)))
("SF_PLANTING" 0 ((4279.78925 1150.07636) (4313.72590 1127.45192)))
("SF_SOLAR" 0 ((4291.10147 8118.40113) (4291.10147 8125.94276) (4283.55916 8133.48416)))
("SF_SOLAR" 0 ((4487.17907 8092.00611) (4464.55464 8088.23529) (4317.49649 8088.24186) (4306.18360 8092.00611)
(4298.64253 8088.23529) (4287.33032 8088.23529)))
("SF_PLANTING" 0 ((4302.41369 354.44853) (4297.44491 377.06810) (4291.10147 384.61538)))
("SF_PLANTING" 0 ((4332.57919 3831.07048) (4294.87138 3831.07048)))
("SF_PLANTING" 0 ((4296.75758 243.21267) (4328.80803 233.93382) (4362.74468 230.16946) (4374.05690 234.84242)
(4392.91143 252.63857)))
("SF_PLANTING" 0 ((4296.75758 243.21267) (4312.67545 271.49321) (4313.72590 301.66007)))
("SF_PLANTING" 0 ((4298.64253 4072.39819) (4298.64253 4015.83710)))
("SF_ARCHITECTURE" 0 ((4325.03812 5527.90305) (4325.03122 4468.32579) (4321.26697 4445.70136) (4321.41505 4389.14027)
(4325.03812 4370.28699) (4321.27319 4219.45701) (4325.03122 4196.83258) (4313.57749 4117.64706) (4298.64253
4072.39819)))
("SF_PLANTING" 0 ((4309.95475 3963.04717) (4298.64253 4015.83710)))
("SF_PLANTING" 0 ((4298.64253 3657.61731) (4317.49581 3657.61731)))
("SF_PLANTING" 0 ((4298.64253 3619.90950) (4284.76391 3642.53394) (4288.38699 3653.69152) (4298.64253 3657.61731)))
("SF_PLANTING" 0 ((4298.64253 3657.61731) (4302.41369 3691.55396)))
("SF_PLANTING" 0 ((4340.12025 3601.05554) (4328.80803 3599.99921) (4306.18360 3585.07805) (4287.48495 3579.78371)
(4284.61584 3589.74333) (4298.64253 3619.90950)))
("SF_PLANTING" 0 ((4321.26697 3634.99287) (4298.64253 3619.90950)))
("SF_MASONRY_AND_ARCH" 0 ((4328.80803 2960.03043) (4298.64253 2960.03043)))
("SF_MASONRY_AND_ARCH" 0 ((4302.41369 3239.06459) (4298.64876 3193.81572) (4298.64253 2960.03043)))
("SF_PLANTING" 0 ((4302.41369 987.93269) (4300.52749 959.65215)))
("SF_PLANTING" 0 ((4300.52749 959.65215) (4336.20192 973.00532) (4347.66256 995.47511)))
("SF_PLANTING" 0 ((4332.57919 3729.26052) (4302.41369 3721.71946)))
("SF_PLANTING" 0 ((4328.80803 3239.06459) (4302.41369 3239.06459)))
("SF_PLANTING" 0 ((4302.41369 987.93269) (4328.80803 995.32738) (4347.66256 995.47511)))
("SF_PLANTING" 0 ((4351.43247 350.67873) (4302.41369 354.44853)))
("SF_SOLAR" 0 ((4309.95475 8058.06946) (4407.99355 8058.07602) (4423.07692 8061.68552) (4438.16029 8058.21742)
(4498.49129 8058.06946)))
("SF_PLANTING" 0 ((4343.89140 3951.73495) (4328.80803 3952.79106) (4309.95475 3963.04717)))
("SF_SOLAR" 0 ((4313.72590 8073.15226) (4313.72590 8080.69389)))
("SF_PLANTING" 0 ((4351.43247 365.76075) (4339.22568 380.84559) (4323.84027 429.86425) (4313.72590 441.17647)))
("SF_PLANTING" 0 ((4321.26697 3634.99287) (4317.49581 3657.61731)))
("SF_PLANTING" 0 ((4343.89140 3672.69943) (4317.49581 3657.61731)))
("SF_ARCHITECTURE" 0 ((6549.77376 6489.44197) (4321.26697 6489.44197)))
("SF_PLANTING" 0 ((4321.26697 3634.99287) (4351.43247 3634.99287)))
("SF_SOLAR" 0 ((4325.03812 8110.85973) (4347.66256 8107.09548) (4377.82805 8110.56357) (4396.68133 8103.47296)
(4415.53586 8106.93439) (4430.61799 8103.47285) (4464.55464 8107.24355) (4475.86686 8114.63054)))
("SF_ARCHITECTURE" 0 ((4325.03812 5527.90305) (4355.20362 5539.06742) (4374.05690 5539.06742) (4404.22364 5524.13314)))
("SF_PLANTING" 0 ((4370.28699 6817.49649) (4365.31165 6798.64253) (4358.96787 6791.24910) (4347.66256 6784.61584)
(4328.80803 6783.55984)))
("SF_MASONRY_AND_ARCH" 0 ((4328.80803 3239.06459) (4325.04434 3216.44016) (4328.80181 3197.58699) (4328.81493
3024.13247) (4332.57919 3001.50803) (4332.43111 2967.57828) (4328.80803 2960.03043)))
("SF_PLANTING" 0 ((4328.80803 3239.06459) (4366.51584 3242.83586)))
("SF_MASONRY_AND_ARCH" 0 ((4328.80803 2960.03043) (4336.35656 2956.40690) (4366.51584 2956.25916)))
("SF_SOLAR" 0 ((4336.35034 8080.69389) (4332.57919 8069.38167)))
("SF_SOLAR" 0 ((4336.35034 8042.98643) (4332.57919 8035.44502)))
("SF_PLANTING" 0 ((4389.14027 3831.07048) (4370.28699 3827.30057) (4332.57919 3831.07048)))
("SF_PLANTING" 0 ((4347.66256 3883.86165) (4337.39989 3865.00713) (4332.57919 3831.07048)))
("SF_PLANTING" 0 ((4332.57919 3729.26052) (4343.89140 3714.17839)))
("SF_PLANTING" 0 ((4332.57919 3729.26052) (4336.50430 3739.51731) (4355.20362 3744.34389)))
("SF_SOLAR" 0 ((4343.89140 8042.98643) (4517.34581 8042.98643)))
("SF_PLANTING" 0 ((4368.40079 3925.33937) (4347.81652 3940.57025) (4343.89140 3951.73495)))
("SF_PLANTING" 0 ((4343.89140 3951.73495) (4353.99943 3963.04717) (4358.81980 3985.67161) (4355.20984 4015.83710)
(4362.59072 4079.93925) (4359.12873 4098.79378) (4362.74468 4121.41821)))
("SF_PLANTING" 0 ((4355.20362 3714.17839) (4343.89140 3714.17839)))
("SF_PLANTING" 0 ((4343.89140 3714.17839) (4343.89140 3672.69943)))
("SF_PLANTING" 0 ((4343.89140 3672.69943) (4358.97477 3672.69943)))
("SF_SOLAR" 0 ((4543.74016 8005.27896) (4347.66256 8005.27896)))
("SF_SOLAR" 0 ((4355.20362 7869.53247) (4347.66256 7869.53247)))
("SF_PLANTING" 0 ((4347.66256 3883.86165) (4355.20362 3883.86165)))
("SF_PLANTING" 0 ((4349.54751 1012.44344) (4347.66256 995.47511)))
("SF_PLANTING" 0 ((4347.66256 946.45645) (4352.48914 935.14423) (4366.51584 920.05939)))
("SF_PLANTING" 0 ((4385.36912 263.95079) (4358.97477 264.10611) (4347.66256 271.49321)))
("SF_PLANTING" 0 ((4349.54751 1012.44344) (4351.43247 1085.97285)))
("SF_PLANTING" 0 ((4349.54751 1012.44344) (4411.76471 1014.32975)))
("SF_PLANTING" 0 ((4351.43247 3774.50939) (4358.97477 3766.96833)))
("SF_PLANTING" 0 ((4404.22364 1134.99152) (4370.28699 1152.78982) (4351.43247 1153.84615)))
("SF_PLANTING" 0 ((4351.43247 1085.97285) (4351.43247 1153.84615)))
("SF_MASONRY_AND_ARCH" 0 ((6546.00328 1157.61595) (6549.76753 1176.47059) (6549.77376 2198.34061) (6545.84864
2213.41719) (6534.69106 2220.81041) (6500.75441 2221.11278) (6459.27602 2229.56312) (6312.21719 2291.55317) (6097.28507
2363.20396) (5818.25011 2431.97896) (5678.73303 2454.60339) (5641.02523 2454.89887) (5592.00645 2462.14514) (5546.75758
2462.44061) (5531.67421 2466.05713) (5377.07432 2466.05713) (5320.51324 2462.14514) (5282.80543 2454.89887) (5248.86878
2454.60339) (5192.30769 2443.58665) (5169.68326 2443.29118) (5116.89333 2432.27443) (5094.26889 2431.97896) (4966.06335
2404.67534) (4766.21459 2348.11425) (4588.98903 2280.24785) (4472.09695 2229.56312) (4441.93020 2224.88405) (4374.05690
2224.58778) (4355.35826 2213.41719) (4355.20362 2202.11188) (4351.43247 1153.84615)))
("SF_PLANTING" 0 ((4351.43247 1085.97285) (4385.36912 1084.91652) (4407.99355 1070.89084)))
("SF_PLANTING" 0 ((4351.43247 365.76075) (4351.43247 350.67873)))
("SF_PLANTING" 0 ((4351.43247 365.76075) (4357.77692 373.31007) (4371.48428 429.85735) (4381.59921 437.40667)))
("SF_PLANTING" 0 ((4351.43247 350.67873) (4361.54740 343.13145) (4373.16233 309.19966) (4385.36912 294.11765)))
("SF_PLANTING" 0 ((4389.14027 3831.07048) (4380.40102 3861.23654) (4355.20362 3883.86165)))
("SF_PLANTING" 0 ((4368.40079 3925.33937) (4360.03394 3914.02715) (4355.20362 3883.86165)))
("SF_PLANTING" 0 ((4355.20362 3714.17839) (4362.44219 3736.79593) (4355.20362 3744.34389)))
("SF_PLANTING" 0 ((4358.97477 3766.96833) (4355.20362 3744.34389)))
("SF_PLANTING" 0 ((4355.20362 3714.17839) (4374.05690 3691.55396)))
("SF_PLANTING" 0 ((4355.20362 3657.61731) (4358.97477 3661.38722) (4358.97477 3672.69943)))
("SF_SOLAR" 0 ((4358.97477 8122.17195) (4358.97477 8133.48416)))
("SF_SOLAR" 0 ((4358.97477 8035.44502) (4358.97477 8016.59118)))
("SF_PLANTING" 0 ((4358.97477 3766.96833) (4381.59921 3782.94627) (4400.44627 3787.02636) (4423.07692 3808.44604)))
("SF_PLANTING" 0 ((4374.05690 3691.55396) (4358.97477 3672.69943)))
("SF_PLANTING" 0 ((4366.51584 3435.14355) (4362.89310 3457.76799) (4367.56561 3468.92557) (4374.05690 3472.85068)))
("SF_PLANTING" 0 ((4366.51584 3408.74785) (4400.30441 3424.88699) (4407.99355 3435.14355)))
("SF_PLANTING" 0 ((4366.51584 3242.83586) (4400.45249 3239.06459)))
("SF_MASONRY_AND_ARCH" 0 ((4366.51584 3242.83586) (4366.51584 2956.25916)))
("SF_MASONRY_AND_ARCH" 0 ((4400.45249 2956.25916) (4366.51584 2956.25916)))
("SF_PLANTING" 0 ((4381.59921 920.05939) (4366.51584 920.05939)))
("SF_PLANTING" 0 ((4368.40079 3925.33937) (4392.91143 3917.79830)))
("SF_PLANTING" 0 ((4368.40079 3925.33937) (4384.16527 3944.19265) (4385.36912 3970.58824)))
("SF_SOLAR" 0 ((4370.28699 7899.69830) (4377.82805 7895.92760)))
("SF_PLANTING" 0 ((4400.45249 4260.93473) (4379.03258 4242.08145) (4370.28699 4208.14480)))
("SF_PLANTING" 0 ((4370.28699 509.04977) (4374.05690 520.36199)))
("SF_SOLAR" 0 ((4377.82805 7895.92760) (4374.05690 7888.38609)))
("SF_PLANTING" 0 ((4400.45249 3697.21007) (4374.05690 3691.55396)))
("SF_SOLAR" 0 ((4619.15577 7907.23982) (4611.60724 7903.61719) (4506.03360 7903.46256) (4487.17907 7899.70486)
(4392.91143 7899.55023) (4377.82805 7895.92760)))
("SF_SOLAR" 0 ((4381.59921 8133.48416) (4381.59921 8122.17195)))
("SF_SOLAR" 0 ((4381.59921 8020.36199) (4381.59921 8035.44502)))
("SF_SOLAR" 0 ((4381.59921 7990.19615) (4381.59921 7982.65452)))
("SF_SOLAR" 0 ((4381.59921 7971.34231) (4566.36459 7971.34231)))
("SF_PLANTING" 0 ((4381.59921 920.05939) (4392.91143 906.03371) (4411.76471 901.20758) (4434.38914 902.26324)
(4468.32579 920.05939)))
("SF_PLANTING" 0 ((4381.59921 920.05939) (4392.91143 938.91403)))
("SF_PLANTING" 0 ((4400.45249 429.86425) (4381.59921 437.40667)))
("SF_PLANTING" 0 ((4400.45249 478.88292) (4399.24796 471.33575) (4382.80305 452.48869) (4381.59921 437.40667)))
("SF_SOLAR" 0 ((4385.36912 7865.76165) (4396.68201 7869.38439) (4472.09695 7869.53247)))
("SF_SOLAR" 0 ((4385.36912 7839.36652) (4453.24242 7839.36652)))
("SF_PLANTING" 0 ((4415.53586 4144.04265) (4408.14853 4121.41821) (4407.84570 4098.79378) (4392.76301 4019.60826)
(4385.51753 4000.75373) (4385.36912 3970.58824)))
("SF_PLANTING" 0 ((4430.61799 3989.44152) (4400.45249 3971.64491) (4385.36912 3970.58824)))
("SF_PLANTING" 0 ((4385.36912 263.95079) (4385.36912 294.11765)))
("SF_PLANTING" 0 ((4407.99355 324.28450) (4404.06867 312.97229) (4385.36912 294.11765)))
("SF_PLANTING" 0 ((4385.36912 263.95079) (4392.91143 252.63857)))
("SF_PLANTING" 0 ((4389.14027 3831.07048) (4415.52896 3826.10271) (4423.07692 3819.75826)))
("SF_PLANTING" 0 ((4404.22364 3367.27025) (4389.14027 3344.64581)))
("SF_SOLAR" 0 ((4392.91143 7933.63495) (4396.68133 7911.01052)))
("SF_SOLAR" 0 ((4392.91143 7933.63495) (4430.61799 7937.39921) (4592.76018 7937.40577)))
("SF_PLANTING" 0 ((4392.91143 3917.79830) (4426.84808 3890.50758) (4453.24242 3887.63156)))
("SF_PLANTING" 0 ((4392.91143 3917.79830) (4407.99355 3931.67658) (4441.93020 3944.19265)))
("SF_PLANTING" 0 ((4392.91143 938.91403) (4393.06538 961.53846) (4396.83631 968.92557) (4415.53518 972.69604)
(4426.84808 965.30826)))
("SF_PLANTING" 0 ((4392.91143 938.91403) (4404.22364 942.68382)))
("SF_PLANTING" 0 ((4400.45249 478.88292) (4392.91143 482.65554)))
("SF_PLANTING" 0 ((4407.99355 252.63857) (4392.91143 252.63857)))
("SF_SOLAR" 0 ((4396.68133 8080.69389) (4396.68133 8069.38167)))
("SF_PLANTING" 0 ((4415.53586 4245.85260) (4411.61007 4257.00984) (4400.45249 4260.93473)))
("SF_ARCHITECTURE" 0 ((4404.22364 5524.13314) (4404.21674 4457.01357) (4400.45249 4434.38914) (4404.21674 4389.14027)
(4404.21674 4287.33032) (4400.45249 4260.93473)))
("SF_PLANTING" 0 ((4400.45249 3697.21007) (4404.21674 3684.01538) (4400.60057 3623.68066) (4407.99355 3608.59729)))
("SF_PLANTING" 0 ((4400.45249 3697.21007) (4405.27907 3729.26052) (4416.58541 3747.96663) (4445.54672 3760.62455)
(4460.78473 3785.82161)))
("SF_PLANTING" 0 ((4426.84808 3706.63609) (4400.45249 3697.21007)))
("SF_PLANTING" 0 ((4436.27410 3239.06459) (4400.45249 3239.06459)))
("SF_MASONRY_AND_ARCH" 0 ((4400.45249 2956.25916) (4400.45249 3239.06459)))
("SF_MASONRY_AND_ARCH" 0 ((4400.45249 2956.25916) (4438.16029 2956.25916)))
("SF_PLANTING" 0 ((4400.45249 478.88292) (4415.53586 520.36199)))
("SF_PLANTING" 0 ((4407.99355 350.67873) (4400.60057 380.84559) (4400.45249 429.86425)))
("SF_PLANTING" 0 ((4400.45249 429.86425) (4419.30577 432.43688) (4434.38914 426.09446)))
("SF_SOLAR" 0 ((4404.22364 8133.48416) (4404.22364 8118.40113)))
("SF_SOLAR" 0 ((4404.22364 8031.67421) (4404.22364 8020.36199)))
("SF_SOLAR" 0 ((4404.22364 7982.65452) (4404.22364 7990.19615)))
("SF_ARCHITECTURE" 0 ((4472.09695 5531.67421) (4464.54842 5535.29695) (4426.84808 5535.29695) (4404.22364 5524.13314)))
("SF_PLANTING" 0 ((4430.61799 1074.66063) (4429.41414 1085.97285) (4410.86957 1112.36708) (4404.22364 1134.99152)))
("SF_PLANTING" 0 ((4407.99400 1195.32523) (4411.61007 1146.30373) (4404.22364 1134.99152)))
("SF_ARCHITECTURE" 0 ((4419.30577 6836.34966) (4426.84762 6874.05758) (4426.84762 7556.56109) (4422.92229 7567.71867)
(4407.99355 7571.64400)))
("SF_PLANTING" 0 ((4447.58631 3608.59729) (4407.99355 3608.59729)))
("SF_PLANTING" 0 ((4419.30577 3540.72398) (4404.22986 3543.59966) (4396.83631 3552.04242) (4396.82975 3574.66063)
(4407.99355 3608.59729)))
("SF_MASONRY_AND_ARCH" 0 ((5015.08337 2665.91278) (4947.21007 2662.14152) (4705.88235 2665.90656) (4690.79898
2662.28925) (4611.61346 2661.99378) (4562.59468 2654.60057) (4423.07692 2658.51946) (4407.99355 2665.91278)))
("SF_PLANTING" 0 ((4415.53586 1048.26640) (4409.19140 1055.81357) (4407.99355 1070.89084)))
("SF_PLANTING" 0 ((4430.61799 1074.66063) (4407.99355 1070.89084)))
("SF_PLANTING" 0 ((4407.99355 350.67873) (4426.84808 350.67873)))
("SF_PLANTING" 0 ((4407.99355 350.67873) (4404.37760 343.13145) (4407.99355 324.28450)))
("SF_PLANTING" 0 ((4426.84808 350.67873) (4425.64333 335.59672) (4415.54208 325.48790) (4407.99355 324.28450)))
("SF_PLANTING" 0 ((4483.40916 233.78676) (4441.93020 231.06505) (4415.54208 242.38348) (4407.99355 252.63857)))
("SF_PLANTING" 0 ((4407.99355 252.63857) (4433.33247 282.80543) (4464.55464 335.59672)))
("SF_PLANTING" 0 ((4407.99400 1195.32523) (4438.15984 1195.32523)))
("SF_MASONRY_AND_ARCH" 0 ((4407.99400 1195.32523) (4408.00045 2115.38462) (4411.61007 2130.46731) (4408.00045
2168.17523) (4412.82138 2183.10328) (4426.84808 2187.02839) (4438.00532 2185.82432) (4441.92398 2175.71618) (4438.15984
2130.46731) (4438.15984 1195.32523)))
("SF_PLANTING" 0 ((4411.76471 1014.32975) (4434.38914 1006.93507) (4464.55464 1006.78733)))
("SF_PLANTING" 0 ((4411.76471 1014.32975) (4415.53586 1048.26640)))
("SF_PLANTING" 0 ((4457.01357 4245.85260) (4415.53586 4245.85260)))
("SF_PLANTING" 0 ((4415.53586 4245.85260) (4415.53586 4144.04265)))
("SF_PLANTING" 0 ((4457.01357 4245.85260) (4460.63631 4238.30407) (4460.63631 4196.83258) (4448.42206 4162.89593)
(4441.78235 4152.64038) (4415.53586 4144.04265)))
("SF_PLANTING" 0 ((4441.93020 1048.26640) (4415.53586 1048.26640)))
("SF_PLANTING" 0 ((4419.30577 6836.34966) (4426.84762 6806.18428) (4426.84762 6564.85645)))
("SF_PLANTING" 0 ((4419.30577 3540.72398) (4427.00204 3521.87692) (4441.93020 3510.55781)))
("SF_PLANTING" 0 ((4441.93020 3552.03620) (4419.30577 3540.72398)))
("SF_MASONRY_AND_ARCH" 0 ((4607.84355 2571.64378) (4596.53066 2575.26731) (4419.30577 2579.18552)))
("SF_SOLAR" 0 ((4423.07692 7854.44943) (4423.07692 7861.99095)))
("SF_PLANTING" 0 ((4423.07692 3819.75826) (4423.07692 3808.44604)))
("SF_PLANTING" 0 ((4423.07692 3819.75826) (4457.01357 3838.61278)))
("SF_PLANTING" 0 ((4460.78473 3785.82161) (4423.07692 3808.44604)))
("SF_PLANTING" 0 ((4423.07692 3457.76799) (4434.38914 3465.30894) (4438.16029 3463.42410)))
("SF_ARCHITECTURE" 0 ((6595.02262 6561.08597) (4449.47251 6561.08597) (4426.84762 6564.85645)))
("SF_SOLAR" 0 ((4426.84808 8133.48416) (4426.84808 8122.17195)))
("SF_SOLAR" 0 ((4426.84808 8080.69389) (4426.84808 8069.38167)))
("SF_SOLAR" 0 ((4426.84808 8020.36199) (4426.84808 8035.44502)))
("SF_SOLAR" 0 ((4426.84808 7990.19615) (4426.84808 7978.88394)))
("SF_SOLAR" 0 ((4426.84808 7944.94717) (4426.84808 7960.03020)))
("SF_SOLAR" 0 ((4430.61799 7914.78133) (4426.84808 7922.32274)))
("SF_PLANTING" 0 ((4438.16029 3408.74785) (4426.84808 3404.97738)))
("SF_PLANTING" 0 ((4460.78473 392.15781) (4450.52794 384.46697) (4426.84808 350.67873)))
("SF_PLANTING" 0 ((4430.61799 3989.44152) (4453.24242 3981.90045)))
("SF_PLANTING" 0 ((4430.61799 3989.44152) (4430.76640 4023.37817) (4446.75113 4076.16934) (4464.55532 4097.73710)
(4483.40916 4105.28507) (4498.49129 4106.33484)))
("SF_PLANTING" 0 ((4441.93020 1048.26640) (4436.96867 1070.73552) (4430.61799 1074.66063)))
("SF_PLANTING" 0 ((4436.27410 3239.06459) (4472.09695 3239.06459)))
("SF_PLANTING" 0 ((4436.27410 3239.06459) (4434.39536 3205.12794) (4438.16029 3182.50351)))
("SF_PLANTING" 0 ((4436.27410 3239.06459) (4438.16029 3273.00124)))
("SF_PLANTING" 0 ((4438.15984 1195.32523) (4449.47251 1157.61595)))
("SF_SOLAR" 0 ((4453.24242 8163.65011) (4449.47251 8171.19163) (4439.36414 8186.27443) (4438.16029 8197.58665)))
("SF_PLANTING" 0 ((4502.26244 3404.97738) (4476.02183 3431.37919) (4460.78405 3453.84208) (4438.16029 3463.42410)))
("SF_PLANTING" 0 ((4438.16029 3408.74785) (4438.16029 3463.42410)))
("SF_PLANTING" 0 ((4441.93020 3510.55781) (4438.16029 3463.42410)))
("SF_PLANTING" 0 ((4438.16029 3408.74785) (4448.27432 3389.89468) (4442.22670 3367.27025) (4445.69514 3340.87455)
(4441.93020 3303.16742)))
("SF_PLANTING" 0 ((4438.16029 3273.00124) (4434.54378 3288.08473) (4441.93020 3303.16742)))
("SF_PLANTING" 0 ((4438.16029 3273.00124) (4464.17998 3289.13416) (4453.24242 3301.96324) (4441.93020 3303.16742)))
("SF_MASONRY_AND_ARCH" 0 ((4438.16029 3182.50351) (4472.09695 3182.50351)))
("SF_MASONRY_AND_ARCH" 0 ((4438.16029 3182.50351) (4438.16029 2956.25916)))
("SF_MASONRY_AND_ARCH" 0 ((4475.86686 2960.03043) (4468.31957 2956.40690) (4438.16029 2956.25916)))
("SF_PLANTING" 0 ((4441.93020 3944.19265) (4446.89242 3933.03541) (4453.24242 3929.11052)))
("SF_PLANTING" 0 ((4453.24242 3970.58824) (4446.89898 3966.66312) (4441.93020 3944.19265)))
("SF_PLANTING" 0 ((4441.93020 3552.03620) (4453.22930 3525.64129) (4452.03857 3518.10645) (4441.93020 3510.55781)))
("SF_PLANTING" 0 ((4447.58631 3608.59729) (4441.93020 3552.03620)))
("SF_PLANTING" 0 ((4441.93020 1048.26640) (4464.55464 1040.72398)))
("SF_PLANTING" 0 ((4447.58631 3608.59729) (4446.90588 3627.30271) (4464.55464 3638.76278)))
("SF_PLANTING" 0 ((4479.63801 3623.68066) (4456.94627 3609.65362) (4447.58631 3608.59729)))
("SF_SOLAR" 0 ((4449.47251 8069.38167) (4449.47251 8080.69389)))
("SF_SOLAR" 0 ((4449.47251 8035.44502) (4449.47251 8016.59118)))
("SF_SOLAR" 0 ((4449.47251 7978.88394) (4449.47251 7993.96674)))
("SF_SOLAR" 0 ((4449.47251 7948.71799) (4449.47251 7960.03020)))
("SF_PLANTING" 0 ((4460.78473 275.26301) (4449.47251 267.72342)))
("SF_SOLAR" 0 ((4490.95023 8163.65011) (4453.24242 8163.65011)))
("SF_SOLAR" 0 ((4457.01357 8144.79638) (4453.24242 8163.65011)))
("SF_PLANTING" 0 ((4453.24242 3970.58824) (4453.24242 3981.90045)))
("SF_PLANTING" 0 ((4483.40916 4030.92048) (4469.37557 4012.06595) (4463.35079 3993.21267) (4453.24242 3981.90045)))
("SF_PLANTING" 0 ((4453.24242 3970.58824) (4483.40916 3955.50486)))
("SF_PLANTING" 0 ((4453.24242 3887.63156) (4453.24242 3929.11052)))
("SF_PLANTING" 0 ((4483.40916 3944.19265) (4453.24242 3929.11052)))
("SF_PLANTING" 0 ((4457.01357 3883.86165) (4457.01357 3887.63156) (4453.24242 3887.63156)))
("SF_PLANTING" 0 ((4457.01357 3883.86165) (4453.24242 3887.63156)))
("SF_SOLAR" 0 ((4619.15577 7907.23982) (4587.93360 7963.80090) (4533.48428 8035.44502) (4489.89355 8110.85973)
(4468.17771 8137.24830) (4457.01357 8144.79638)))
("SF_PLANTING" 0 ((4457.01357 4245.85260) (4461.84084 4272.24695) (4477.05848 4302.25871) (4483.40916 4306.18360)))
("SF_PLANTING" 0 ((4457.01357 3883.86165) (4494.57296 3878.88597) (4503.45351 3861.39118) (4509.80351 3857.46606)))
("SF_PLANTING" 0 ((4457.01357 3883.86165) (4457.01357 3838.61278)))
("SF_PLANTING" 0 ((4498.49129 3834.84163) (4457.01357 3838.61278)))
("SF_MASONRY_AND_ARCH" 0 ((4457.01357 2349.17070) (4453.53891 2334.08722) (4457.01357 2315.23382)))
("SF_MASONRY_AND_ARCH" 0 ((4528.65803 2315.23382) (4498.49129 2315.23382) (4457.01357 2315.23382)))
("SF_PLANTING" 0 ((4460.78473 3785.82161) (4494.72138 3789.59276)))
("SF_MASONRY_AND_ARCH" 0 ((4460.78473 2439.66844) (4460.93258 2522.61753) (4464.55464 2530.16618)))
("SF_MASONRY_AND_ARCH" 0 ((4460.78473 2024.88688) (4460.78473 1983.40848)))
("SF_PLANTING" 0 ((4460.78473 392.15781) (4490.95023 384.61538)))
("SF_PLANTING" 0 ((4460.78473 392.15781) (4464.55464 403.47002)))
("SF_PLANTING" 0 ((4479.63801 3623.68066) (4464.55464 3638.76278)))
("SF_PLANTING" 0 ((4464.55464 3638.76278) (4457.16821 3653.84615) (4457.16165 3668.92952) (4468.32579 3691.55396)))
("SF_MASONRY_AND_ARCH" 0 ((4464.55464 2631.97613) (4475.86686 2628.20486)))
("SF_MASONRY_AND_ARCH" 0 ((4464.55464 2549.01934) (4464.55464 2530.16618)))
("SF_MASONRY_AND_ARCH" 0 ((4973.60441 2530.16618) (4966.05713 2526.54955) (4950.97998 2529.86991) (4932.12670
2526.39491) (4860.48224 2526.69118) (4849.17002 2530.01154) (4638.00905 2526.39491) (4615.38462 2530.15995) (4464.55464
2530.16618)))
("SF_PLANTING" 0 ((4464.55464 1006.78733) (4464.55464 1040.72398)))
("SF_PLANTING" 0 ((4502.26244 1089.74265) (4483.26075 1059.57862) (4464.55464 1040.72398)))
("SF_PLANTING" 0 ((4472.09695 1003.01753) (4464.55464 1006.78733)))
("SF_PLANTING" 0 ((4464.55464 335.59672) (4464.55464 343.13631)))
("SF_PLANTING" 0 ((4464.55464 335.59672) (4483.40916 324.28450)))
("SF_SOLAR" 0 ((4468.32579 7854.44943) (4472.09695 7869.53247)))
("SF_PLANTING" 0 ((4536.19910 3729.26052) (4517.34581 3721.87410) (4483.40916 3731.67975) (4463.03835 3710.40724)
(4468.32579 3691.55396)))
("SF_PLANTING" 0 ((4494.72138 3699.09502) (4487.17285 3691.70792) (4468.32579 3691.55396)))
("SF_PLANTING" 0 ((4513.57466 912.51980) (4487.17907 912.66686) (4468.32579 920.05939)))
("SF_PLANTING" 0 ((4475.86686 946.45645) (4468.32579 920.05939)))
("SF_SOLAR" 0 ((4472.09695 8080.69389) (4472.09695 8069.38167)))
("SF_SOLAR" 0 ((4472.09695 8031.67421) (4472.09695 8020.36199)))
("SF_SOLAR" 0 ((4472.09695 7990.19615) (4472.09695 7978.88394)))
("SF_SOLAR" 0 ((4472.09695 7948.71799) (4472.09695 7960.03020)))
("SF_SOLAR" 0 ((4472.09695 7869.53247) (4490.95023 7868.47624) (4502.26244 7861.99095)))
("SF_ARCHITECTURE" 0 ((4472.09695 5531.67421) (4502.26244 5527.90305)))
("SF_ARCHITECTURE" 0 ((4472.09695 5531.67421) (4460.78428 5512.82093) (4460.78428 5475.11312) (4468.33201 5463.80090)
(4487.17907 5448.71753)))
("SF_PLANTING" 0 ((4472.09695 3239.06459) (4509.80351 3239.06459)))
("SF_PLANTING" 0 ((4472.09695 3239.06459) (4475.86063 3216.44016) (4472.09695 3182.50351)))
("SF_MASONRY_AND_ARCH" 0 ((4475.86686 2960.03043) (4475.86063 3141.02590) (4472.09695 3182.50351)))
("SF_PLANTING" 0 ((4475.86686 946.45645) (4472.24480 954.00362) (4472.09695 1003.01753)))
("SF_PLANTING" 0 ((4472.09695 1003.01753) (4509.80351 1011.75577) (4551.28247 1027.52545)))
("SF_PLANTING" 0 ((4506.03360 3465.30894) (4509.64253 3476.62115) (4505.87862 3484.00826) (4490.95023 3490.65441)
(4475.86686 3491.70464)))
("SF_MASONRY_AND_ARCH" 0 ((4475.86686 2960.03043) (4490.95023 2956.25916) (4509.80351 2960.03043)))
("SF_MASONRY_AND_ARCH" 0 ((4475.86686 2628.20486) (4479.63801 2620.66391)))
("SF_MASONRY_AND_ARCH" 0 ((4475.86686 2628.20486) (4498.49129 2635.59819) (4521.11572 2635.74661)))
("SF_PLANTING" 0 ((4475.86686 946.45645) (4490.95023 956.56380) (4513.57466 961.53846)))
("SF_ARCHITECTURE" 0 ((7315.23405 7582.95622) (7296.38009 7571.79208) (7239.81900 7567.87986) (7209.65283 7571.64400)
(4487.18597 7570.43971) (4479.63801 7556.56109) (4479.63801 6602.56437) (4479.63801 6591.25215)))
("SF_PLANTING" 0 ((4479.63801 3623.68066) (4487.17907 3619.90950)))
("SF_PLANTING" 0 ((4479.63801 422.32183) (4489.75260 414.77466) (4493.67093 403.47002) (4490.95023 384.61538)))
("SF_MASONRY_AND_ARCH" 0 ((4483.40871 2190.79966) (4479.64423 1168.92817) (4488.37692 1142.54084) (4498.49129
1134.99152)))
("SF_PLANTING" 0 ((4483.40916 4306.18360) (4516.14106 4287.17568) (4517.19740 4264.70588) (4513.57466 4253.39367)))
("SF_ARCHITECTURE" 0 ((4487.17907 5282.80543) (4487.17285 4355.20362) (4483.40916 4306.18360)))
("SF_PLANTING" 0 ((4498.49129 4027.14932) (4487.17907 4027.14932) (4483.40916 4030.92048)))
("SF_PLANTING" 0 ((4498.49129 4087.48156) (4488.22952 4061.08597) (4483.40916 4030.92048)))
("SF_PLANTING" 0 ((4483.40916 3944.19265) (4483.40916 3955.50486)))
("SF_PLANTING" 0 ((4519.23077 3974.35939) (4483.40916 3955.50486)))
("SF_PLANTING" 0 ((4513.57466 3936.65158) (4498.49129 3937.70136) (4483.40916 3944.19265)))
("SF_PLANTING" 0 ((4483.40916 233.78676) (4502.26244 230.01414) (4547.51131 233.78676)))
("SF_PLANTING" 0 ((4483.40916 233.78676) (4487.33405 256.41120) (4502.26244 270.43688) (4524.88688 282.80543)))
("SF_ARCHITECTURE" 0 ((4487.17907 5411.01097) (4487.17907 5448.71753)))
("SF_ARCHITECTURE" 0 ((4502.26244 5527.90305) (4502.11437 5482.65419) (4493.52353 5456.26606) (4487.17907 5448.71753)))
("SF_ARCHITECTURE" 0 ((4487.17907 5282.80543) (4497.43518 5297.88880) (4498.34344 5369.53201) (4494.56640 5399.69808)
(4487.17907 5411.01097)))
("SF_ARCHITECTURE" 0 ((4487.17907 5282.80543) (4460.78428 5301.65871) (4460.78428 5316.74208) (4460.78428 5384.61538)
(4468.47387 5395.92760) (4487.17907 5411.01097)))
("SF_PLANTING" 0 ((4562.59468 3612.36776) (4487.17907 3619.90950)))
("SF_PLANTING" 0 ((4487.17907 3619.90950) (4487.17907 3582.20238)))
("SF_PLANTING" 0 ((4509.80351 3574.66063) (4487.17907 3582.20238)))
("SF_PLANTING" 0 ((4498.49129 3525.64129) (4479.79265 3544.49446) (4473.15305 3559.57794) (4473.30735 3567.11889)
(4487.17907 3582.20238)))
("SF_SOLAR" 0 ((4490.95023 8163.65011) (4502.26244 8163.65011) (4702.11120 8163.65011)))
("SF_SOLAR" 0 ((4490.95023 8163.65011) (4509.80351 8137.25498)))
("SF_SOLAR" 0 ((4490.95023 7843.13722) (4517.34581 7854.30136) (4592.76018 7850.82681) (4630.46109 7854.60407)
(4638.00905 7861.99095)))
("SF_PLANTING" 0 ((4524.88688 365.76075) (4498.49819 374.35950) (4490.95023 384.61538)))
("SF_SOLAR" 0 ((4494.72138 8122.17195) (4490.95023 8125.94276) (4494.72138 8137.25498)))
("SF_SOLAR" 0 ((4494.72138 7978.88394) (4494.72138 7990.19615)))
("SF_SOLAR" 0 ((4494.72138 7948.71799) (4494.72138 7960.03020)))
("SF_PLANTING" 0 ((4536.19910 3736.80283) (4520.06618 3774.36154) (4494.72138 3789.59276)))
("SF_PLANTING" 0 ((4498.49129 3834.84163) (4494.86923 3823.52941) (4494.72138 3789.59276)))
("SF_SOLAR" 0 ((4498.49129 8035.44502) (4498.49129 8020.36199)))
("SF_PLANTING" 0 ((4498.49129 4132.73043) (4498.49129 4106.33484)))
("SF_PLANTING" 0 ((4513.57466 4253.39367) (4492.00690 4241.93337) (4483.55701 4223.22817) (4479.93450 4189.29152)
(4488.23575 4147.81256) (4498.49129 4132.73043)))
("SF_PLANTING" 0 ((4513.57466 4253.39367) (4517.19740 4245.84570) (4517.19740 4177.97930) (4512.37014 4147.81256)
(4498.49129 4132.73043)))
("SF_PLANTING" 0 ((4498.49129 4087.48156) (4498.49129 4106.33484)))
("SF_PLANTING" 0 ((4570.13575 4125.18812) (4558.97817 4117.64084) (4543.74016 4096.22681) (4513.57466 4087.62941)
(4498.49129 4087.48156)))
("SF_PLANTING" 0 ((4498.49129 4027.14932) (4519.23077 3974.35939)))
("SF_PLANTING" 0 ((4498.49129 4027.14932) (4509.80419 4034.53643) (4551.28247 4038.46154)))
("SF_PLANTING" 0 ((4498.49129 3834.84163) (4509.80351 3857.46606)))
("SF_PLANTING" 0 ((4502.26244 1089.74265) (4498.63971 1101.05486) (4498.49129 1134.99152)))
("SF_PLANTING" 0 ((4513.57466 1165.15837) (4498.49129 1134.99152)))
("SF_ARCHITECTURE" 0 ((4502.26244 5527.90305) (4517.34581 5539.06131) (4551.28247 5539.06742) (4573.90690 5531.67421)))
("SF_PLANTING" 0 ((4577.67681 1134.99152) (4543.74016 1105.87624) (4502.26244 1089.74265)))
("SF_SOLAR" 0 ((4509.80351 8137.25498) (4550.08428 8073.15894) (4551.28247 8065.61086)))
("SF_SOLAR" 0 ((4702.11120 8141.02557) (4521.11640 8141.01900) (4509.80351 8137.25498)))
("SF_SOLAR" 0 ((4517.34581 8107.08891) (4509.80351 8103.31833) (4509.80351 8095.77670)))
("SF_PLANTING" 0 ((4536.19910 3861.23722) (4509.80351 3857.46606)))
("SF_MASONRY_AND_ARCH" 0 ((4509.80351 2960.03043) (4509.79729 3197.58699) (4506.03982 3216.44016) (4509.80351
3239.06459)))
("SF_PLANTING" 0 ((4539.97025 3239.06459) (4521.11640 3242.82274) (4509.80351 3239.06459)))
("SF_MASONRY_AND_ARCH" 0 ((4539.97025 2956.25916) (4509.80351 2960.03043)))
("SF_PLANTING" 0 ((4513.57466 3936.65158) (4524.88688 3936.65158)))
("SF_PLANTING" 0 ((4513.57466 3936.65158) (4513.57466 3898.94378)))
("SF_MASONRY_AND_ARCH" 0 ((4513.57466 1165.15837) (4517.34536 2055.05305) (4517.34536 2073.90622) (4521.27070
2187.02217) (4528.65803 2194.57014)))
("SF_PLANTING" 0 ((4513.57466 1165.15837) (4536.19910 1173.75645) (4547.51131 1187.78281)))
("SF_PLANTING" 0 ((4513.57466 961.53846) (4517.34581 946.45645) (4513.57466 912.51980)))
("SF_PLANTING" 0 ((4513.57466 961.53846) (4528.65803 975.56482) (4551.28247 987.93269)))
("SF_PLANTING" 0 ((4513.57466 912.51980) (4543.74016 901.35464) (4570.13575 901.35532) (4592.76018 916.28959)))
("SF_SOLAR" 0 ((4517.34581 7948.71799) (4517.34581 7960.03020)))
("SF_PLANTING" 0 ((4581.44796 3966.81708) (4519.23077 3974.35939)))
("SF_PLANTING" 0 ((4519.23077 3974.35939) (4524.88688 3936.65158)))
("SF_SOLAR" 0 ((4521.11572 7982.65452) (4521.11572 7990.19615)))
("SF_PLANTING" 0 ((4521.11572 3657.61731) (4521.11572 3665.15837)))
("SF_SOLAR" 0 ((4536.19910 8080.69389) (4524.88688 8084.46448)))
("SF_PLANTING" 0 ((4555.05238 3929.11052) (4524.88688 3936.65158)))
("SF_PLANTING" 0 ((4524.88688 365.76075) (4532.28009 343.13631) (4528.65803 305.42986)))
("SF_PLANTING" 0 ((4524.88688 365.76075) (4554.00317 411.00962) (4581.44796 467.57070)))
("SF_PLANTING" 0 ((4547.51131 233.78676) (4541.16753 245.09898) (4538.91357 263.95079) (4524.88688 282.80543)))
("SF_PLANTING" 0 ((4528.65803 305.42986) (4524.88688 282.80543)))
("SF_PLANTING" 0 ((4528.65803 305.42986) (4562.59468 305.42986)))
("SF_SOLAR" 0 ((4536.19910 8058.06946) (4543.74016 8058.06946) (4551.28247 8065.61086)))
("SF_PLANTING" 0 ((4536.19910 3729.26052) (4536.19910 3736.80283)))
("SF_PLANTING" 0 ((4592.76018 3746.22885) (4581.44796 3740.72455) (4547.51131 3740.42489) (4536.19910 3736.80283)))
("SF_PLANTING" 0 ((4536.19910 3729.26052) (4566.36459 3650.07500)))
("SF_MASONRY_AND_ARCH" 0 ((4539.97025 2956.25916) (4539.97647 3065.61086) (4543.74016 3088.23529) (4539.97025
3239.06459)))
("SF_PLANTING" 0 ((4577.67681 3239.06459) (4562.59468 3242.82896) (4539.97025 3239.06459)))
("SF_MASONRY_AND_ARCH" 0 ((4539.97025 2956.25916) (4577.67681 2956.25916)))
("SF_SOLAR" 0 ((4732.27794 8103.31833) (4630.46799 8103.31176) (4604.07240 8099.54751) (4547.51131 8103.31833)))
("SF_MASONRY_AND_ARCH" 0 ((4555.05238 2202.11188) (4551.28201 2171.94570) (4551.28201 2051.28179) (4551.28201
2036.19910) (4551.28201 2002.26244) (4551.28201 1941.93088) (4551.28201 1923.07692) (4551.28201 1870.28631) (4551.28201
1847.66188) (4547.51131 1187.78281)))
("SF_MASONRY_AND_ARCH" 0 ((4607.84310 2190.79966) (4592.76640 2189.59548) (4585.22534 2175.71618) (4581.44174
1278.28054) (4577.82523 1263.19853) (4577.52285 1195.33009) (4570.12952 1187.93744) (4547.51131 1187.78281)))
("SF_PLANTING" 0 ((4604.07240 237.55656) (4547.51131 233.78676)))
("SF_SOLAR" 0 ((4562.59468 8058.06946) (4551.28247 8065.61086)))
("SF_PLANTING" 0 ((4573.90690 4019.60826) (4555.20735 4027.30396) (4551.28247 4038.46154)))
("SF_PLANTING" 0 ((4581.44796 4076.16934) (4556.25713 4060.93790) (4551.28247 4038.46154)))
("SF_PLANTING" 0 ((4592.76018 1018.09955) (4566.36459 1018.25419) (4551.28247 1027.52545)))
("SF_PLANTING" 0 ((4551.28247 987.93269) (4551.28247 1027.52545)))
("SF_PLANTING" 0 ((4551.28247 1027.52545) (4555.05238 1052.03620)))
("SF_PLANTING" 0 ((4551.28247 987.93269) (4577.67681 980.39310)))
("SF_PLANTING" 0 ((4585.21912 3921.56821) (4566.36527 3921.72319) (4555.05238 3929.11052)))
("SF_PLANTING" 0 ((4555.05238 3929.11052) (4562.59468 3944.19265)))
("SF_PLANTING" 0 ((4573.90690 1052.03620) (4555.05238 1052.03620)))
("SF_PLANTING" 0 ((4596.53133 1116.13971) (4585.07070 1101.20328) (4567.42127 1089.59559) (4555.05238 1052.03620)))
("SF_SOLAR" 0 ((4558.82353 7948.71799) (4558.82353 7963.80090)))
("SF_PLANTING" 0 ((4592.76018 3876.31934) (4558.82353 3865.00713)))
("SF_SOLAR" 0 ((4562.59468 8118.40113) (4562.59468 8125.94276)))
("SF_SOLAR" 0 ((4562.59468 8058.06946) (4574.96233 8031.67421) (4651.88767 7926.09355) (4653.09242 7911.01052)))
("SF_SOLAR" 0 ((4562.59468 8058.06946) (4675.71686 8058.07602) (4690.79898 8061.69208) (4762.43722 8061.98812)
(4769.98450 8065.61086)))
("SF_PLANTING" 0 ((4570.13575 3951.73495) (4566.36459 3951.73495) (4562.59468 3944.19265)))
("SF_PLANTING" 0 ((4570.13575 3951.73495) (4570.13575 3947.96380) (4562.59468 3944.19265)))
("SF_PLANTING" 0 ((4562.59468 3612.36776) (4573.90000 3602.25973) (4581.44796 3601.05554)))
("SF_PLANTING" 0 ((4562.59468 3612.36776) (4566.36459 3650.07500)))
("SF_PLANTING" 0 ((4566.36459 286.57523) (4562.59468 305.42986)))
("SF_PLANTING" 0 ((4622.92568 350.67873) (4600.30124 345.70407) (4585.21912 334.54649) (4562.59468 305.42986)))
("SF_PLANTING" 0 ((4600.30124 3646.30509) (4566.36459 3650.07500)))
("SF_PLANTING" 0 ((4570.13575 4147.81256) (4570.13575 4125.18812)))
("SF_ARCHITECTURE" 0 ((4570.13575 4147.81256) (4570.28382 4208.14480) (4573.90000 4223.22817) (4573.90000 4634.23790)
(4570.13575 4656.86233) (4570.14197 4758.67229) (4573.90000 4777.52681) (4573.90000 5196.07885) (4570.14197 5214.93213)
(4570.13575 5414.78088) (4573.90000 5437.40532) (4573.90690 5531.67421)))
("SF_PLANTING" 0 ((4600.30124 4151.58371) (4570.13575 4147.81256)))
("SF_PLANTING" 0 ((4570.13575 4125.18812) (4585.06414 4106.33484) (4585.07070 4083.71663) (4581.44796 4076.16934)))
("SF_PLANTING" 0 ((4581.44796 3959.27602) (4570.13575 3951.73495)))
("SF_PLANTING" 0 ((4570.13575 365.76075) (4584.02749 384.61538) (4601.35792 422.32183) (4630.46799 448.71889)))
("SF_SOLAR" 0 ((4573.90690 8005.27896) (4581.44796 8005.27896)))
("SF_ARCHITECTURE" 0 ((4645.55011 5535.44536) (4634.23790 5539.06742) (4596.53133 5539.06742) (4573.90690 5531.67421)))
("SF_PLANTING" 0 ((4573.90690 4019.60826) (4577.67681 4012.06595)))
("SF_PLANTING" 0 ((4581.44796 4076.16934) (4585.07070 4068.62081) (4585.06414 4038.46154) (4573.90690 4019.60826)))
("SF_PLANTING" 0 ((4592.76018 1018.09955) (4573.90690 1052.03620)))
("SF_PLANTING" 0 ((4573.90690 1052.03620) (4592.76018 1069.68597) (4630.46731 1077.23326) (4641.78020 1074.66063)))
("SF_PLANTING" 0 ((4573.90690 961.53846) (4577.67681 980.39310)))
("SF_SOLAR" 0 ((4581.44796 7914.78133) (4577.67681 7922.32274)))
("SF_PLANTING" 0 ((4581.44796 3966.81708) (4577.67681 4012.06595)))
("SF_PLANTING" 0 ((4649.32127 4013.95215) (4577.67681 4012.06595)))
("SF_PLANTING" 0 ((4577.67681 3239.06459) (4607.84355 3239.06459)))
("SF_MASONRY_AND_ARCH" 0 ((4577.67681 3239.06459) (4577.67681 2956.25916)))
("SF_MASONRY_AND_ARCH" 0 ((4577.67681 2956.25916) (4607.84355 2960.03043)))
("SF_PLANTING" 0 ((4577.67681 1134.99152) (4596.53133 1116.13971)))
("SF_PLANTING" 0 ((4577.67681 1134.99152) (4592.76018 1152.64129) (4615.38462 1157.31425) (4626.69683 1150.07636)))
("SF_PLANTING" 0 ((4683.25792 965.30826) (4671.79106 946.61663) (4664.40396 943.88869) (4645.55011 947.65984)
(4604.07240 975.56482) (4577.67681 980.39310)))
("SF_PLANTING" 0 ((4592.76018 916.28959) (4582.50464 927.60181) (4577.67681 942.68382)))
("SF_PLANTING" 0 ((4581.44796 3966.81708) (4581.44796 3959.27602)))
("SF_PLANTING" 0 ((4585.21912 3921.56821) (4588.84118 3929.11674) (4588.83507 3951.72805) (4581.44796 3959.27602)))
("SF_PLANTING" 0 ((4581.44796 3601.05554) (4581.44796 3593.51459) (4588.98903 3589.74333)))
("SF_PLANTING" 0 ((4581.44796 3601.05554) (4600.30124 3623.68066)))
("SF_SOLAR" 0 ((4585.21912 8133.48416) (4585.21912 8118.40113)))
("SF_SOLAR" 0 ((4585.21912 8069.38167) (4585.21912 8080.69389)))
("SF_PLANTING" 0 ((4592.76018 3876.31934) (4585.36697 3898.94378) (4585.21912 3921.56821)))
("SF_PLANTING" 0 ((4596.53133 3717.94830) (4588.98903 3699.09502)))
("SF_PLANTING" 0 ((4588.98903 3589.74333) (4607.84355 3588.68699) (4626.69683 3579.63529) (4649.32127 3585.97285)))
("SF_PLANTING" 0 ((4596.53133 3552.03620) (4588.98903 3589.74333)))
("SF_PLANTING" 0 ((4588.98903 3533.18224) (4596.53133 3552.03620)))
("SF_PLANTING" 0 ((4592.76018 3876.31934) (4600.30124 3876.31934)))
("SF_PLANTING" 0 ((4596.53133 3717.94830) (4592.76018 3746.22885)))
("SF_PLANTING" 0 ((4611.61346 3823.52941) (4604.21391 3819.60430) (4597.58744 3808.44604) (4592.76018 3746.22885)))
("SF_PLANTING" 0 ((4592.76018 3746.22885) (4626.69683 3748.11505)))
("SF_PLANTING" 0 ((4592.76018 1018.09955) (4630.46799 1006.93507) (4660.63348 1006.78733)))
("SF_PLANTING" 0 ((4713.42342 916.28959) (4698.34061 902.26324) (4668.17455 897.59027) (4630.46799 902.25633)
(4592.76018 916.28959)))
("SF_PLANTING" 0 ((4596.53133 3717.94830) (4638.00905 3717.94830)))
("SF_PLANTING" 0 ((4596.53133 3552.03620) (4604.07240 3552.03620)))
("SF_PLANTING" 0 ((4596.53133 1116.13971) (4615.22998 1131.22172) (4626.69683 1150.07636)))
("SF_SOLAR" 0 ((4607.84355 7971.34231) (4600.30124 7967.57172)))
("SF_PLANTING" 0 ((4600.30124 3876.31934) (4611.61346 3823.52941)))
("SF_PLANTING" 0 ((4754.90238 3865.00713) (4732.27794 3886.58201) (4709.65351 3898.79593) (4664.40464 3898.79593)
(4600.30124 3876.31934)))
("SF_PLANTING" 0 ((4600.30124 3646.30509) (4600.30124 3623.68066)))
("SF_PLANTING" 0 ((4600.30124 3646.30509) (4607.84977 3656.56063) (4622.92568 3661.38722)))
("SF_PLANTING" 0 ((4600.30124 3623.68066) (4626.54876 3624.88450) (4638.00905 3642.53394)))
("SF_SOLAR" 0 ((4604.07240 8012.82059) (4630.46799 8009.05633) (4645.55011 8012.67251) (4796.38009 8016.43654)
(4807.53767 8009.04321) (4811.46346 7997.73756)))
("SF_MASONRY_AND_ARCH" 0 ((4604.07240 2635.74661) (4615.38462 2631.98235) (4834.08790 2631.97613)))
("SF_PLANTING" 0 ((4698.34129 260.18100) (4671.94570 234.99016) (4656.86233 231.06437) (4634.23790 230.16256)
(4604.07240 237.55656)))
("SF_PLANTING" 0 ((4604.07240 237.55656) (4604.22048 267.72342) (4611.61346 297.88744)))
("SF_MASONRY_AND_ARCH" 0 ((4607.84310 2190.79966) (4607.84310 2179.48744)))
("SF_MASONRY_AND_ARCH" 0 ((4607.84310 2190.79966) (4645.55011 2198.34061)))
("SF_MASONRY_AND_ARCH" 0 ((4641.78020 1184.01301) (4615.39084 1188.98767) (4607.84310 1202.86482) (4607.84310
2164.40396)))
("SF_SOLAR" 0 ((4607.84355 8118.40113) (4607.84355 8133.48416)))
("SF_SOLAR" 0 ((4607.84355 8069.38167) (4607.84355 8084.46448)))
("SF_SOLAR" 0 ((4607.84355 8042.98643) (4683.25792 8042.97986) (4709.65351 8039.21561) (4762.44344 8039.36369)
(4777.52681 8042.98643)))
("SF_SOLAR" 0 ((4607.84355 8027.90339) (4607.84355 8035.44502)))
("SF_PLANTING" 0 ((4607.84355 3239.06459) (4649.32127 3239.06459)))
("SF_MASONRY_AND_ARCH" 0 ((4607.84355 3239.06459) (4607.84355 2960.03043)))
("SF_MASONRY_AND_ARCH" 0 ((4649.32127 2960.03043) (4634.23790 2956.25916) (4607.84355 2960.03043)))
("SF_PLANTING" 0 ((4607.84355 490.19514) (4615.38462 490.19514)))
("SF_PLANTING" 0 ((4611.61346 3823.52941) (4622.92636 3819.60430) (4645.39615 3797.13382) (4653.09242 3778.28054)))
("SF_PLANTING" 0 ((4611.61346 512.81957) (4615.38462 490.19514)))
("SF_PLANTING" 0 ((4656.86233 290.34785) (4641.78020 281.14762) (4611.61346 297.88744)))
("SF_PLANTING" 0 ((4615.38462 312.97229) (4611.61346 297.88744)))
("SF_SOLAR" 0 ((4622.92568 7944.94717) (4615.38462 7944.94717)))
("SF_PLANTING" 0 ((4615.38462 490.19514) (4622.92568 482.65554)))
("SF_SOLAR" 0 ((4619.15577 7907.23982) (4634.23790 7899.85950) (4653.09242 7903.46256) (4781.29672 7903.46256)
(4803.92115 7899.69830) (4871.79446 7903.46256) (4905.73111 7895.92760)))
("SF_PLANTING" 0 ((4622.92568 3661.38722) (4638.00905 3642.53394)))
("SF_PLANTING" 0 ((4622.92568 3661.38722) (4624.13043 3668.93575) (4641.78020 3687.78281)))
("SF_PLANTING" 0 ((4622.92568 350.67873) (4631.66527 331.82410) (4655.65848 305.42986) (4656.86233 290.34785)))
("SF_PLANTING" 0 ((4622.92568 350.67873) (4638.00905 361.99095)))
("SF_PLANTING" 0 ((4638.00905 3733.03167) (4626.69683 3748.11505)))
("SF_PLANTING" 0 ((4653.09242 3778.28054) (4635.28835 3763.04932) (4626.69683 3748.11505)))
("SF_PLANTING" 0 ((4641.78020 1151.95984) (4626.69683 1150.07636)))
("SF_SOLAR" 0 ((4630.46799 8125.94276) (4630.46799 8118.40113)))
("SF_SOLAR" 0 ((4630.46799 8020.36199) (4630.46799 8035.44502)))
("SF_SOLAR" 0 ((4830.31674 7971.34231) (4822.76878 7964.99208) (4800.15124 7960.03020) (4758.67229 7960.17828)
(4709.65351 7971.19434) (4630.46799 7971.34231)))
("SF_PLANTING" 0 ((4705.88235 309.19966) (4694.71821 316.74898) (4688.07862 328.05430) (4659.58371 411.00962)
(4645.40226 433.63405) (4630.46799 448.71889)))
("SF_PLANTING" 0 ((4641.78020 467.57070) (4635.42952 463.64627) (4630.46799 448.71889)))
("SF_SOLAR" 0 ((4653.09242 8001.50837) (4634.23790 8001.50837)))
("SF_SOLAR" 0 ((4894.41889 7850.67873) (4868.02455 7854.44287) (4664.40464 7854.60407) (4645.70509 7869.53247)
(4634.23790 7888.38609)))
("SF_PLANTING" 0 ((4638.00905 3947.96380) (4642.82941 3959.12138) (4649.32127 3963.04717)))
("SF_PLANTING" 0 ((4638.00905 3733.03167) (4638.00905 3717.94830)))
("SF_PLANTING" 0 ((4638.00905 3733.03167) (4656.86233 3741.77059) (4675.71686 3759.42726)))
("SF_PLANTING" 0 ((4645.55011 3710.40724) (4638.00905 3717.94830)))
("SF_PLANTING" 0 ((4653.09242 3642.53394) (4638.00905 3642.53394)))
("SF_SOLAR" 0 ((4641.78020 8084.46448) (4641.78020 8073.15226)))
("SF_PLANTING" 0 ((4641.78020 4113.87590) (4653.09242 4106.33484)))
("SF_PLANTING" 0 ((4660.63348 3672.69943) (4641.78020 3687.78281)))
("SF_PLANTING" 0 ((4645.55011 3710.40724) (4641.78020 3687.78281)))
("SF_PLANTING" 0 ((4641.78020 1151.95984) (4641.78020 1184.01301)))
("SF_MASONRY_AND_ARCH" 0 ((4641.78020 1184.01301) (4649.32127 1195.32523) (4645.55011 2198.34061)))
("SF_PLANTING" 0 ((4641.78020 1151.95984) (4649.32127 1097.28507)))
("SF_PLANTING" 0 ((4641.78020 1151.95984) (4675.71618 1152.64129) (4698.34129 1128.50758) (4717.19457 1123.67930)))
("SF_PLANTING" 0 ((4660.63348 1044.49378) (4646.74830 1055.80600) (4641.78020 1074.66063)))
("SF_PLANTING" 0 ((4641.78020 1074.66063) (4649.32127 1097.28507)))
("SF_ARCHITECTURE" 0 ((4645.55011 5599.54751) (4656.86301 5588.23529) (4702.11120 5588.23529)))
("SF_ARCHITECTURE" 0 ((4645.55011 5599.54751) (4664.40464 5617.04887) (4679.48676 5614.78484) (4694.56391 5618.24638)
(4702.11120 5614.63088)))
("SF_ARCHITECTURE" 0 ((4645.55011 5535.44536) (4645.55011 5094.26889)))
("SF_ARCHITECTURE" 0 ((6236.80215 5535.44536) (6217.94898 5539.21527) (4720.96572 5539.20905) (4705.88235 5535.59321)
(4645.55011 5535.44536)))
("SF_ARCHITECTURE" 0 ((4653.09242 5049.02002) (4645.70509 5056.56731) (4645.55011 5094.26889)))
("SF_ARCHITECTURE" 0 ((4645.55011 5094.26889) (4687.02907 5099.08925) (4792.60894 5142.23846) (4819.00452 5148.11550)
(4977.37557 5202.56324) (5098.03880 5233.63756) (5139.51776 5237.55656)))
("SF_PLANTING" 0 ((4645.55011 3710.40724) (4668.16833 3710.25916) (4675.71686 3706.63609)))
("SF_MASONRY_AND_ARCH" 0 ((5237.55656 2364.25339) (5180.99548 2360.33518) (5150.82998 2349.31912) (5037.70781
2330.16900) (4913.27342 2299.09423) (4739.81900 2242.53314) (4656.86301 2208.45498) (4645.55011 2198.34061)))
("SF_PLANTING" 0 ((4649.32127 4013.95215) (4649.32127 3963.04717)))
("SF_PLANTING" 0 ((4649.32127 4013.95215) (4653.09242 4106.33484)))
("SF_PLANTING" 0 ((4649.32127 4013.95215) (4675.71686 4015.83710)))
("SF_PLANTING" 0 ((4649.32127 3963.04717) (4709.65351 3932.88043)))
("SF_PLANTING" 0 ((4664.40464 3616.13903) (4678.28292 3608.44887) (4676.61143 3593.52081) (4664.40396 3583.40645)
(4649.32127 3585.97285)))
("SF_PLANTING" 0 ((4664.40464 3616.13903) (4654.28971 3604.82681) (4649.32127 3585.97285)))
("SF_PLANTING" 0 ((4687.02907 3239.06459) (4649.32127 3239.06459)))
("SF_MASONRY_AND_ARCH" 0 ((4649.32127 2960.03043) (4649.32127 3239.06459)))
("SF_MASONRY_AND_ARCH" 0 ((4649.32127 2960.03043) (4656.86923 2956.40690) (4687.02907 2956.25916)))
("SF_PLANTING" 0 ((4660.63348 1093.51527) (4649.32127 1097.28507)))
("SF_SOLAR" 0 ((4653.09242 8118.40113) (4653.09242 8133.48416)))
("SF_SOLAR" 0 ((4653.09242 8035.44502) (4653.09242 8020.36199)))
("SF_SOLAR" 0 ((4653.09242 7982.65452) (4653.09242 7990.19615)))
("SF_PLANTING" 0 ((4653.09242 5049.02002) (4653.09864 4177.97930) (4656.86233 4155.35486) (4656.71448 4113.88281)
(4653.09242 4106.33484)))
("SF_ARCHITECTURE" 0 ((4653.09242 5049.02002) (4698.34129 5074.21708) (4792.60894 5110.40147) (4807.69231 5119.46595)
(4864.25339 5135.74661)))
("SF_PLANTING" 0 ((4675.71686 3759.42726) (4668.02670 3773.45328) (4653.09242 3778.28054)))
("SF_PLANTING" 0 ((4653.09242 3642.53394) (4664.40464 3616.13903)))
("SF_PLANTING" 0 ((4653.09242 3642.53394) (4659.57681 3657.61731) (4660.63348 3672.69943)))
("SF_SOLAR" 0 ((4852.94118 7937.40577) (4656.86233 7937.40577)))
("SF_PLANTING" 0 ((4698.34129 260.18100) (4675.71686 282.65079) (4656.86233 290.34785)))
("SF_PLANTING" 0 ((4660.63348 3672.69943) (4674.66018 3691.55396) (4675.71686 3706.63609)))
("SF_PLANTING" 0 ((4660.63348 1006.78733) (4660.63348 1044.49378)))
("SF_PLANTING" 0 ((4717.19457 1070.89084) (4690.95396 1069.68597) (4679.33891 1049.46980) (4660.63348 1044.49378)))
("SF_PLANTING" 0 ((4683.25792 965.30826) (4673.00238 976.62048) (4660.63348 1006.78733)))
("SF_PLANTING" 0 ((4664.40464 512.81957) (4773.75566 516.59219)))
("SF_SOLAR" 0 ((4675.71686 8122.17195) (4675.71686 8114.63054)))
("SF_SOLAR" 0 ((4675.71686 8069.38167) (4675.71686 8084.46448)))
("SF_SOLAR" 0 ((4675.71686 8020.36199) (4675.71686 8031.67421)))
("SF_SOLAR" 0 ((4675.71686 7978.88394) (4675.71686 7990.19615)))
("SF_PLANTING" 0 ((4758.67229 3932.88043) (4733.47523 3944.34762) (4717.04649 3981.90045) (4675.71686 4015.83710)))
("SF_PLANTING" 0 ((4675.71686 4015.83710) (4702.11120 4046.00260)))
("SF_PLANTING" 0 ((4675.71686 3759.42726) (4686.88066 3758.22251) (4713.42342 3725.49061)))
("SF_PLANTING" 0 ((4709.65351 3711.03586) (4698.48224 3706.80905) (4675.71686 3706.63609)))
("SF_SOLAR" 0 ((4713.42342 8088.23529) (4683.25792 8088.23529)))
("SF_PLANTING" 0 ((4690.79898 3540.72398) (4683.25792 3506.78733)))
("SF_PLANTING" 0 ((4683.25792 965.30826) (4702.11120 965.30826)))
("SF_PLANTING" 0 ((4747.36007 3227.75238) (4724.73563 3238.91618) (4687.02907 3239.06459)))
("SF_MASONRY_AND_ARCH" 0 ((4687.02907 3239.06459) (4687.02907 2956.25916)))
("SF_MASONRY_AND_ARCH" 0 ((4743.59016 2963.80090) (4724.73563 2956.40769) (4687.02907 2956.25916)))
("SF_SOLAR" 0 ((4698.34129 8118.40113) (4690.79898 8133.48416)))
("SF_MASONRY_AND_ARCH" 0 ((4690.79898 2145.55079) (4709.65351 2141.77952)))
("SF_SOLAR" 0 ((4694.57014 7918.55204) (4698.34129 7926.09355)))
("SF_SOLAR" 0 ((4694.57014 7843.13722) (4702.11120 7843.13722)))
("SF_SOLAR" 0 ((4698.34129 8069.38167) (4698.34129 8080.69389)))
("SF_SOLAR" 0 ((4698.34129 8031.67421) (4698.34129 8020.36199)))
("SF_SOLAR" 0 ((4698.34129 7978.88394) (4698.34129 7990.19615)))
("SF_SOLAR" 0 ((4698.34129 7948.71799) (4698.34129 7956.25939)))
("SF_PLANTING" 0 ((4698.34129 260.18100) (4709.65351 260.18100)))
("SF_SOLAR" 0 ((4702.11120 8163.65011) (4769.98450 8065.61086)))
("SF_SOLAR" 0 ((4702.11120 8163.65011) (4709.65973 8169.99400) (4724.73563 8172.85645) (4747.36007 8159.87941)))
("SF_ARCHITECTURE" 0 ((4702.11120 5588.23529) (4702.11120 5614.63088)))
("SF_ARCHITECTURE" 0 ((4822.77568 5610.85973) (4807.69231 5618.39457) (4717.19457 5618.39457) (4702.11120 5614.63088)))
("SF_ARCHITECTURE" 0 ((4822.77568 5595.77636) (4792.60894 5588.23529) (4702.11120 5588.23529)))
("SF_PLANTING" 0 ((4702.11120 965.30826) (4702.25962 950.22624) (4713.42342 916.28959)))
("SF_PLANTING" 0 ((4713.42342 987.93269) (4702.11120 965.30826)))
("SF_MASONRY_AND_ARCH" 0 ((4717.19457 2269.98518) (4705.88235 2269.98518)))
("SF_PLANTING" 0 ((4705.88235 309.19966) (4706.03699 290.34785) (4713.42342 279.03563)))
("SF_PLANTING" 0 ((4758.67229 437.40667) (4733.33337 384.61538) (4715.99038 320.51188) (4705.88235 309.19966)))
("SF_SOLAR" 0 ((4709.65351 8197.58665) (4709.65351 8182.50385)))
("SF_PLANTING" 0 ((4709.65351 3711.03586) (4717.19457 3710.40724) (4717.19457 3706.63609)))
("SF_PLANTING" 0 ((4709.65351 3711.03586) (4717.19457 3706.63609)))
("SF_PLANTING" 0 ((4751.13122 3608.59729) (4728.50679 3609.80147) (4714.47387 3627.45057) (4706.03043 3650.07500)
(4706.03043 3699.26109) (4709.65351 3711.03586)))
("SF_PLANTING" 1 ((4709.65351 3711.03586) (4709.65351 3717.94830) (4705.88235 3714.17839)))
("SF_PLANTING" 0 ((4709.65351 3711.03586) (4713.42342 3725.49061)))
("SF_MASONRY_AND_ARCH" 0 ((4709.65351 2141.77952) (4709.80136 2122.92636) (4717.19457 2092.76018) (4717.19457
1776.01810) (4717.19457 1757.16346) (4717.20079 1168.92817) (4720.96572 1146.30373) (4717.19457 1123.67930)))
("SF_MASONRY_AND_ARCH" 0 ((4709.65351 2141.77952) (4754.90238 2167.12568) (4868.02455 2212.36765) (5045.24887
2262.29570) (5226.24434 2296.23235) (5305.42986 2300.29830) (5354.44989 2307.54457) (5456.25984 2307.69231)))
("SF_PLANTING" 0 ((4709.65351 260.18100) (4728.50679 238.76143) (4781.29672 237.55656)))
("SF_PLANTING" 0 ((4713.42342 279.03563) (4709.65351 260.18100)))
("SF_PLANTING" 0 ((4724.73563 4038.46154) (4713.42342 4053.54491)))
("SF_PLANTING" 0 ((4713.42342 3725.49061) (4731.07975 3740.57274) (4743.59016 3785.82161)))
("SF_PLANTING" 0 ((4713.42342 987.93269) (4703.47025 1025.64197) (4720.96572 1040.72398)))
("SF_PLANTING" 0 ((4713.42342 987.93269) (4732.27726 992.61256) (4743.59016 1003.01753)))
("SF_PLANTING" 0 ((4720.96572 916.28959) (4713.42342 916.28959)))
("SF_PLANTING" 0 ((4713.42342 279.03563) (4739.67093 294.27229) (4758.67229 335.59672)))
("SF_PLANTING" 0 ((4751.13122 3608.59729) (4753.70452 3619.90950) (4750.07455 3650.07500) (4738.76923 3676.47059)
(4717.19457 3706.63609)))
("SF_PLANTING" 0 ((4717.19457 1070.89084) (4720.96572 1097.28507) (4717.19457 1123.67930)))
("SF_PLANTING" 0 ((4717.19457 1070.89084) (4720.81731 1063.34152) (4720.96572 1040.72398)))
("SF_SOLAR" 0 ((4724.73563 8069.38167) (4720.96572 8080.69389)))
("SF_SOLAR" 0 ((4720.96572 8020.36199) (4720.96572 8031.67421)))
("SF_SOLAR" 0 ((4811.46346 7997.73756) (4792.60894 7993.96674) (4720.96572 7997.73756)))
("SF_SOLAR" 0 ((4720.96572 7978.88394) (4720.96572 7990.19615)))
("SF_PLANTING" 0 ((4736.04785 1040.72398) (4720.96572 1040.72398)))
("SF_PLANTING" 0 ((4720.96572 916.28959) (4736.04785 905.13201) (4788.83903 908.74717)))
("SF_PLANTING" 0 ((4773.75566 961.53846) (4758.66606 942.83224) (4739.81900 933.94559) (4720.96572 916.28959)))
("SF_SOLAR" 0 ((4739.81900 8148.56719) (4732.27794 8144.79638)))
("SF_PLANTING" 0 ((4736.04785 1040.72398) (4733.47523 1025.64197) (4743.59016 1003.01753)))
("SF_PLANTING" 0 ((4766.21459 1044.49378) (4736.04785 1040.72398)))
("SF_SOLAR" 0 ((4743.59016 7975.11312) (4743.59016 7986.42534)))
("SF_PLANTING" 0 ((4743.59016 3785.82161) (4777.52681 3785.82161)))
("SF_PLANTING" 0 ((4754.90238 3857.46606) (4733.47523 3831.07048) (4725.03903 3800.90498) (4728.66143 3793.51176)
(4743.59016 3785.82161)))
("SF_MASONRY_AND_ARCH" 0 ((4743.59016 2963.80090) (4762.44344 2956.40769) (4800.15124 2956.25916)))
("SF_MASONRY_AND_ARCH" 0 ((4747.36007 3227.75238) (4743.59638 3178.73303) (4743.59016 2963.80090)))
("SF_PLANTING" 0 ((4743.59016 1003.01753) (4762.44344 1003.01753)))
("SF_SOLAR" 0 ((4819.00452 8061.84005) (4804.97161 8073.15238) (4747.36007 8159.87941)))
("SF_SOLAR" 0 ((4996.22885 8163.65000) (4762.44344 8163.64344) (4747.36007 8159.87941)))
("SF_SOLAR" 0 ((4747.36007 8122.17195) (4751.13122 8129.71335)))
("SF_PLANTING" 0 ((4747.36007 3227.75238) (4766.21459 3238.90995) (4800.15124 3239.06459)))
("SF_ARCHITECTURE" 0 ((4751.13122 5041.47771) (4773.75566 5041.47771)))
("SF_PLANTING" 0 ((4751.13122 3608.59729) (4773.75566 3603.77036) (4783.86335 3597.13665) (4785.21595 3578.43111)
(4792.60894 3559.57794)))
("SF_PLANTING" 0 ((4754.90238 3857.46606) (4754.90238 3865.00713)))
("SF_PLANTING" 0 ((4754.90238 3865.00713) (4772.55113 3883.86165) (4777.52681 3914.02715)))
("SF_PLANTING" 0 ((4754.90238 3857.46606) (4785.06787 3846.15385)))
("SF_SOLAR" 0 ((4758.67229 8031.67421) (4762.44344 8024.13281)))
("SF_PLANTING" 0 ((4758.67229 3932.88043) (4777.52681 3914.02715)))
("SF_ARCHITECTURE" 0 ((4758.67229 3932.88043) (4762.44344 3947.96380) (4762.44344 4030.92048) (4762.44344 4049.77376)
(4759.87704 5003.77048) (4769.98518 5013.87862) (4981.14672 5089.44796) (5056.56109 5109.20317) (5267.72206 5146.91075)
(5407.23982 5158.22296) (5456.25984 5158.37104)))
("SF_PLANTING" 0 ((4826.54559 426.09446) (4778.57602 380.84559) (4763.49321 358.22115) (4758.67229 335.59672)))
("SF_PLANTING" 0 ((4852.94118 358.22115) (4819.00452 358.06584) (4781.29672 336.65238) (4758.67229 335.59672)))
("SF_SOLAR" 0 ((4762.44344 8099.54751) (4773.75566 8103.31833)))
("SF_MASONRY_AND_ARCH" 0 ((4762.44344 2292.60962) (4777.52681 2292.60962)))
("SF_PLANTING" 0 ((4773.75566 961.53846) (4762.44344 1003.01753)))
("SF_PLANTING" 0 ((4769.98450 1014.32975) (4762.44344 1003.01753)))
("SF_SOLAR" 0 ((4766.21459 7978.88394) (4766.21459 7986.42534)))
("SF_PLANTING" 0 ((4766.21459 1044.49378) (4766.21459 1055.80600)))
("SF_MASONRY_AND_ARCH" 0 ((4785.06787 2088.98971) (4767.41188 2085.06380) (4762.44966 2066.36527) (4766.20769
2024.88688) (4762.44344 1414.02715) (4769.98495 1391.40271) (4766.21459 1055.80600)))
("SF_PLANTING" 0 ((4785.06787 1063.34842) (4766.21459 1055.80600)))
("SF_PLANTING" 0 ((4766.21459 1044.49378) (4769.83665 1036.94661) (4769.98450 1014.32975)))
("SF_SOLAR" 0 ((5000.00000 8144.79638) (4988.68778 8141.03213) (4769.98450 8141.02557)))
("SF_SOLAR" 0 ((4796.38009 8024.13281) (4769.98450 8065.61086)))
("SF_PLANTING" 0 ((4769.98450 1014.32975) (4803.92115 1013.27262) (4837.85781 984.16290)))
("SF_PLANTING" 0 ((4773.75566 961.53846) (4796.38009 957.76867)))
("SF_PLANTING" 0 ((4777.52681 3914.02715) (4807.69231 3925.33937)))
("SF_PLANTING" 0 ((4796.38009 3710.40724) (4799.99627 3748.11505) (4777.52681 3785.82161)))
("SF_PLANTING" 0 ((4834.08790 3808.44604) (4792.60894 3796.07839) (4777.52681 3785.82161)))
("SF_PLANTING" 0 ((4856.71233 245.09898) (4845.39943 234.99016) (4822.77568 230.16256) (4796.38009 230.16256)
(4781.29672 237.55656)))
("SF_PLANTING" 0 ((4811.46346 279.03563) (4788.99299 260.18100) (4781.29672 237.55656)))
("SF_MASONRY_AND_ARCH" 0 ((4785.06787 2088.98971) (4789.89514 2104.06550) (4796.38631 2110.40995) (4815.22715
2111.46640) (4822.77568 2107.84287)))
("SF_MASONRY_AND_ARCH" 0 ((4785.06787 2088.98971) (4811.45656 2091.86538) (4822.77568 2107.84287)))
("SF_SOLAR" 0 ((4792.60894 7975.11312) (4788.83903 7986.42534)))
("SF_PLANTING" 0 ((4849.17002 904.97738) (4803.92115 905.12511) (4788.83903 908.74717)))
("SF_PLANTING" 0 ((4796.38009 957.76867) (4796.23201 935.14423) (4788.83903 908.74717)))
("SF_PLANTING" 0 ((4792.60894 3661.38722) (4841.62896 3687.78281)))
("SF_MASONRY_AND_ARCH" 0 ((4792.60894 2303.92183) (4803.92115 2303.92183) (4807.69231 2307.69231)))
("SF_PLANTING" 0 ((4792.60894 463.80090) (4803.92115 467.57070)))
("SF_PLANTING" 0 ((4792.60894 312.97229) (4796.53473 314.49468) (4811.46346 305.42986)))
("SF_SOLAR" 0 ((4796.38009 8103.31833) (4830.31674 8099.54751) (5015.08337 8103.31833)))
("SF_PLANTING" 0 ((4796.38009 957.76867) (4811.46346 958.97206) (4837.85781 984.16290)))
("SF_PLANTING" 0 ((4837.85781 3239.06459) (4800.15124 3239.06459)))
("SF_MASONRY_AND_ARCH" 0 ((4800.15124 3239.06459) (4800.15124 2956.25916)))
("SF_MASONRY_AND_ARCH" 0 ((4845.40011 2960.03043) (4837.85158 2956.40690) (4800.15124 2956.25916)))
("SF_PLANTING" 0 ((4800.15124 1070.89084) (4822.77568 1089.58179) (4845.40011 1082.20305)))
("SF_SOLAR" 0 ((4811.46346 8118.40113) (4803.92115 8133.48416)))
("SF_PLANTING" 0 ((4826.54559 452.48869) (4815.38179 453.69355) (4803.92115 467.57070)))
("SF_PLANTING" 0 ((4803.92115 467.57070) (4830.31674 493.96776)))
("SF_PLANTING" 0 ((4807.69231 4000.75373) (4803.92115 3978.12930) (4807.69231 3925.33937)))
("SF_ARCHITECTURE" 0 ((4807.69231 4000.75373) (4811.46346 4068.62704) (4811.45656 4905.73111) (4807.69853 4950.97998)
(4811.61742 4962.28597) (4822.77568 4969.83450)))
("SF_PLANTING" 0 ((4856.71233 4046.00260) (4871.79446 4052.49446) (4882.95271 4052.34016) (4886.72319 4045.99638)
(4885.67330 4030.92048) (4868.02455 4012.21437) (4849.17002 4001.81041) (4807.69231 4000.75373)))
("SF_PLANTING" 0 ((4807.69231 3925.33937) (4825.34830 3902.71493) (4826.54559 3887.63156)))
("SF_PLANTING" 0 ((4807.69231 3880.09050) (4826.54559 3887.63156)))
("SF_SOLAR" 0 ((4811.46346 7997.73756) (4825.48948 7982.65464) (4830.31674 7971.34231)))
("SF_PLANTING" 0 ((4811.46346 279.03563) (4811.46346 305.42986)))
("SF_PLANTING" 0 ((4852.94118 328.05430) (4834.23575 319.45622) (4826.39774 310.39830) (4811.46346 305.42986)))
("SF_PLANTING" 0 ((4811.46346 279.03563) (4849.17002 275.26301)))
("SF_SOLAR" 0 ((4822.77568 8031.67421) (4815.23337 8024.13281)))
("SF_SOLAR" 0 ((4819.00452 8061.84005) (4852.94118 8058.06957) (4875.56561 8061.83348) (4901.96120 8058.22398)
(4917.04333 8061.83348) (5022.62443 8061.83348) (5037.70781 8058.36550) (5052.78993 8061.84005)))
("SF_SOLAR" 0 ((4819.00452 8061.84005) (4820.20215 8050.52783) (4861.53269 7986.42534) (4920.81448 7914.78133)))
("SF_MASONRY_AND_ARCH" 0 ((4819.00452 2594.26821) (4826.55249 2583.11063) (4834.08790 2579.34016) (4996.22885
2575.26731) (5007.54106 2571.64378)))
("SF_ARCHITECTURE" 0 ((4822.77568 5595.77636) (4822.77568 5610.85973)))
("SF_ARCHITECTURE" 0 ((4856.71233 5599.54751) (4841.62896 5617.19005) (4822.77568 5610.85973)))
("SF_ARCHITECTURE" 0 ((4822.77568 5595.77636) (4849.16380 5595.92477) (4856.71233 5599.54751)))
("SF_ARCHITECTURE" 0 ((4822.77568 4969.83450) (4841.62274 4967.26787) (4852.94118 4984.91663)))
("SF_ARCHITECTURE" 0 ((4822.77568 4969.83450) (4830.46482 4983.71278) (4852.94118 4984.91663)))
("SF_MASONRY_AND_ARCH" 0 ((4822.77568 2315.23405) (4834.08790 2315.23405) (4837.85781 2319.00452)))
("SF_MASONRY_AND_ARCH" 0 ((4822.77568 2107.84287) (4920.81448 2144.49434) (5018.85328 2174.66674) (5188.53654
2213.27636) (5290.34649 2224.73631)))
("SF_PLANTING" 0 ((4898.19005 3887.63156) (4826.54559 3887.63156)))
("SF_PLANTING" 0 ((4826.54559 452.48869) (4826.54559 426.09446)))
("SF_PLANTING" 0 ((4826.54559 452.48869) (4837.70995 460.03597) (4845.24514 475.11312) (4841.47432 486.41844)
(4830.31674 493.96776)))
("SF_PLANTING" 0 ((4826.54559 426.09446) (4837.85848 422.16855) (4856.71233 403.47002)))
("SF_SOLAR" 0 ((4852.94118 7937.40577) (4844.34344 7956.25939) (4830.31674 7971.34231)))
("SF_SOLAR" 0 ((4830.31674 7926.09355) (4834.08790 7914.78133)))
("SF_PLANTING" 0 ((4830.31674 509.04977) (4830.31674 493.96776)))
("SF_SOLAR" 0 ((4834.08790 8084.46448) (4837.85781 8073.15226)))
("SF_PLANTING" 0 ((4845.40011 3978.12930) (4841.62896 3970.58824) (4834.08790 3966.81708)))
("SF_PLANTING" 0 ((4913.27342 3819.75826) (4852.94118 3804.82398) (4834.08790 3808.44604)))
("SF_PLANTING" 0 ((4834.08790 3808.44604) (4835.14400 3823.52941) (4841.77704 3834.83541) (4868.01765 3852.49762)
(4875.56561 3853.69491)))
("SF_PLANTING" 0 ((4837.85781 3239.06459) (4860.48224 3239.06459)))
("SF_PLANTING" 0 ((4852.94118 3186.27477) (4839.06256 3197.58699) (4837.85781 3239.06459)))
("SF_PLANTING" 0 ((4852.94118 984.16290) (4837.85781 984.16290)))
("SF_PLANTING" 0 ((4901.96120 3665.15837) (4886.72975 3643.59061) (4868.02455 3636.19672) (4856.86629 3642.68201)
(4853.10238 3650.07568) (4856.40894 3683.85769) (4841.62896 3687.78281)))
("SF_PLANTING" 0 ((4841.62896 3687.78281) (4846.59740 3710.40724) (4856.71233 3721.71946)))
("SF_MASONRY_AND_ARCH" 0 ((4856.71233 2960.03043) (4845.40011 2960.03043)))
("SF_MASONRY_AND_ARCH" 0 ((4845.40011 2960.03043) (4838.01278 2975.11312) (4838.01278 3005.27930) (4841.78360
3012.81403) (4852.94118 3020.36199)))
("SF_PLANTING" 0 ((4845.40011 1036.95419) (4856.71233 1040.72398)))
("SF_PLANTING" 0 ((4849.17002 904.97738) (4856.71233 931.37161)))
("SF_PLANTING" 0 ((4894.41889 908.74717) (4883.10667 905.12511) (4849.17002 904.97738)))
("SF_PLANTING" 0 ((4856.71233 245.09898) (4850.22670 256.41120) (4849.17002 275.26301)))
("SF_PLANTING" 0 ((4864.25339 294.11765) (4856.85328 290.19253) (4849.17002 275.26301)))
("SF_SOLAR" 0 ((4856.71233 8084.46448) (4852.94118 8069.38167)))
("SF_SOLAR" 0 ((4852.94118 7963.80090) (4864.25339 7967.57172)))
("SF_SOLAR" 0 ((4868.02455 7914.78133) (4866.81980 7922.32941) (4852.94118 7937.40577)))
("SF_ARCHITECTURE" 0 ((4954.75113 5015.08337) (4852.94118 4984.91663)))
("SF_MASONRY_AND_ARCH" 0 ((4852.94118 3186.27477) (4852.94118 3020.36199)))
("SF_PLANTING" 0 ((4852.94118 3186.27477) (4864.10532 3208.89921) (4860.48224 3239.06459)))
("SF_MASONRY_AND_ARCH" 0 ((4856.71233 2960.03043) (4864.09876 2975.11312) (4864.09876 3005.27930) (4852.94118
3020.36199)))
("SF_MASONRY_AND_ARCH" 0 ((4852.94118 2631.97613) (4864.25339 2631.97613) (4871.79446 2631.97613) (4984.91663
2631.98235) (4996.22885 2635.74661)))
("SF_PLANTING" 0 ((4901.96120 976.62048) (4864.25339 976.77579) (4852.94118 984.16290)))
("SF_PLANTING" 0 ((4856.71233 1040.72398) (4860.32828 999.24491) (4852.94118 984.16290)))
("SF_PLANTING" 0 ((4852.94118 358.22115) (4852.94118 328.05430)))
("SF_PLANTING" 0 ((4860.48224 361.99095) (4852.94118 358.22115)))
("SF_PLANTING" 0 ((4864.25339 294.11765) (4863.04921 316.74208) (4852.94118 328.05430)))
("SF_SOLAR" 0 ((4856.71233 8042.98643) (4939.66776 8039.21561) (5064.10215 8042.98643)))
("SF_ARCHITECTURE" 0 ((4856.71233 5599.54751) (5527.90305 5599.55373) (5546.75758 5603.31176) (5633.48416 5603.31867)))
("SF_PLANTING" 0 ((4856.71233 3925.33937) (4860.48224 3936.65158)))
("SF_PLANTING" 0 ((4879.33676 3714.17839) (4856.71233 3721.71946)))
("SF_PLANTING" 0 ((4913.27342 3778.28054) (4886.87783 3769.54129) (4859.58767 3740.57274) (4856.71233 3721.71946)))
("SF_MASONRY_AND_ARCH" 0 ((4856.71233 2960.03043) (4864.25962 2956.40690) (4901.96120 2956.41380) (4917.04333
2963.80090)))
("SF_MASONRY_AND_ARCH" 0 ((4856.71233 2326.54627) (4909.50226 2338.91482) (4932.12670 2348.12048) (4954.75113
2350.22014) (4981.14672 2360.33439) (5124.43439 2386.73009) (5147.05882 2387.02557) (5237.55656 2401.81278) (5377.07432
2413.12500) (5580.69423 2409.35452) (5754.14740 2386.73009) (5818.25011 2371.79514)))
("SF_PLANTING" 0 ((4856.71233 1040.72398) (4860.63722 1050.83903) (4878.96776 1060.62738) (4879.33676 1082.20305)))
("SF_PLANTING" 0 ((4935.89785 367.64706) (4917.04333 374.35950) (4883.10667 398.64864) (4856.71233 403.47002)))
("SF_PLANTING" 0 ((4856.71233 403.47002) (4860.48224 361.99095)))
("SF_PLANTING" 0 ((4856.71233 245.09898) (4890.64830 245.25226) (4901.96120 252.63857)))
("SF_PLANTING" 0 ((4917.04333 3235.29412) (4898.19005 3242.68733) (4860.48224 3239.06459)))
("SF_PLANTING" 0 ((4879.33676 1082.20305) (4861.68699 1097.28507) (4860.48224 1116.13971)))
("SF_PLANTING" 0 ((4860.48224 361.99095) (4883.10667 354.29525) (4908.29808 324.28937) (4909.50226 316.74208)))
("SF_SOLAR" 0 ((5090.49774 8005.27896) (5045.24887 8001.51493) (4924.58563 8001.36029) (4909.50226 7997.74412)
(4864.25339 8001.50837)))
("SF_PLANTING" 0 ((4969.83450 3917.79830) (4950.83213 3944.19265) (4924.58563 3965.61980) (4890.64898 3974.19785)
(4864.25339 3951.73495)))
("SF_PLANTING" 0 ((4864.25339 294.11765) (4879.33676 289.14921) (4894.41889 275.26301)))
("SF_SOLAR" 0 ((4879.33676 8016.59118) (4871.79446 8035.44502)))
("SF_PLANTING" 0 ((4886.87783 3921.56821) (4875.56561 3921.56821)))
("SF_SOLAR" 0 ((4879.33676 8069.38167) (4879.33676 8084.46448)))
("SF_SOLAR" 0 ((4879.33676 7929.86425) (4890.64898 7933.63495)))
("SF_ARCHITECTURE" 0 ((4879.33676 5143.28767) (4898.19005 5143.28767)))
("SF_PLANTING" 0 ((4898.19005 1101.05486) (4879.33676 1082.20305)))
("SF_PLANTING" 0 ((4898.19005 3887.63156) (4896.99242 3902.71493) (4886.87783 3921.56821)))
("SF_PLANTING" 0 ((4890.64898 3929.11052) (4886.87783 3921.56821)))
("SF_SOLAR" 0 ((5109.35102 7975.11312) (5098.03880 7971.34887) (4890.64898 7967.57172)))
("SF_PLANTING" 0 ((4894.41889 908.74717) (4890.64898 923.83201)))
("SF_SOLAR" 0 ((4894.41889 7843.13722) (4917.04333 7843.13722)))
("SF_PLANTING" 0 ((5041.47771 916.28959) (5011.31222 912.37138) (4973.60441 901.35464) (4920.81448 901.35464)
(4894.41889 908.74717)))
("SF_PLANTING" 0 ((4901.96120 252.63857) (4894.41889 275.26301)))
("SF_PLANTING" 0 ((4894.41889 275.26301) (4909.50226 316.74208)))
("SF_PLANTING" 0 ((4969.83450 3917.79830) (4935.89785 3892.45249) (4920.81448 3887.77998) (4898.19005 3887.63156)))
("SF_SOLAR" 0 ((4901.96120 8016.59118) (4901.96120 8031.67421)))
("SF_SOLAR" 0 ((4905.73111 7978.88394) (4901.96120 7986.42534)))
("SF_PLANTING" 0 ((4909.50226 3714.17839) (4902.10905 3691.55396) (4901.96120 3665.15837)))
("SF_PLANTING" 0 ((4901.96120 3665.15837) (4924.57873 3665.31301) (4931.07002 3669.08348) (4935.74943 3680.24174)
(4935.89785 3699.09502)))
("SF_PLANTING" 0 ((4901.96120 976.62048) (4920.81448 972.99910) (4943.43891 984.16290)))
("SF_PLANTING" 0 ((4901.96120 976.62048) (4903.16505 999.24005) (4920.81448 1010.55713)))
("SF_PLANTING" 0 ((4901.96120 516.59219) (4939.66776 516.59219)))
("SF_PLANTING" 0 ((4901.96120 252.63857) (4909.50226 252.63857)))
("SF_SOLAR" 0 ((4924.58563 7865.76165) (4923.38744 7873.30973) (4905.73111 7895.92760)))
("SF_SOLAR" 0 ((5158.37104 7903.46912) (4924.58563 7903.46256) (4905.73111 7895.92760)))
("SF_PLANTING" 0 ((4909.50226 3714.17839) (4928.35554 3714.17839)))
("SF_PLANTING" 0 ((4909.50226 3714.17839) (4903.15848 3721.72568) (4900.44400 3736.79593) (4917.04333 3751.88495)))
("SF_PLANTING" 0 ((4950.97998 286.57523) (4924.58563 311.91516) (4909.50226 316.74208)))
("SF_PLANTING" 0 ((4984.91663 241.32636) (4954.75113 230.31109) (4928.35554 234.99016) (4909.50226 252.63857)))
("SF_PLANTING" 0 ((4950.97998 286.57523) (4909.50226 252.63857)))
("SF_SOLAR" 0 ((4913.27342 8069.38167) (4913.27342 8084.46448)))
("SF_PLANTING" 0 ((4913.27342 3819.75826) (4913.27342 3849.92500)))
("SF_PLANTING" 0 ((4932.12670 3812.21719) (4913.27342 3819.75826)))
("SF_PLANTING" 0 ((4913.27342 3778.28054) (4917.04333 3751.88495)))
("SF_PLANTING" 0 ((4913.27342 3778.28054) (4920.96256 3793.35701) (4932.12670 3800.90498)))
("SF_SOLAR" 0 ((4917.04333 7937.40577) (5131.97545 7937.40577)))
("SF_SOLAR" 0 ((4924.58563 7865.76165) (4917.04333 7858.22025)))
("SF_ARCHITECTURE" 0 ((4928.35554 5154.59989) (4917.04333 5154.59989)))
("SF_PLANTING" 0 ((4917.04333 3751.88495) (4932.12670 3751.88495)))
("SF_MASONRY_AND_ARCH" 0 ((4917.04333 3235.29412) (4917.04333 2963.80090)))
("SF_PLANTING" 0 ((4917.04333 3235.29412) (4939.66776 3242.68812) (4962.28597 3242.68812) (4969.83450 3239.06459)))
("SF_MASONRY_AND_ARCH" 0 ((4973.60441 2956.25916) (4932.12670 2956.41380) (4917.04333 2963.80090)))
("SF_PLANTING" 0 ((4920.81448 1010.55713) (4931.07070 1002.86912) (4943.43891 984.16290)))
("SF_PLANTING" 0 ((4928.35554 1040.72398) (4920.81448 1010.55713)))
("SF_SOLAR" 0 ((4928.35554 7944.94717) (4924.58563 7952.48869)))
("SF_SOLAR" 0 ((4924.58563 7865.76165) (4947.21007 7854.59751) (5030.16550 7854.30136) (5049.02002 7850.67873)
(5196.07885 7854.44287) (5211.16097 7850.67873)))
("SF_PLANTING" 0 ((4935.89785 3699.09502) (4928.35554 3714.17839)))
("SF_PLANTING" 0 ((4928.35554 3714.17839) (4932.12670 3751.88495)))
("SF_PLANTING" 0 ((4928.35554 1040.72398) (4928.35554 1052.03620)))
("SF_PLANTING" 0 ((4928.35554 1040.72398) (4962.29219 1029.41176)))
("SF_PLANTING" 0 ((4932.12670 3812.21719) (4932.12670 3800.90498)))
("SF_PLANTING" 0 ((4932.12670 3812.21719) (4954.75113 3824.72704) (4973.60441 3841.32658) (4988.68778 3846.15385)))
("SF_PLANTING" 0 ((4947.21007 3755.65611) (4946.00532 3785.82161) (4932.12670 3800.90498)))
("SF_PLANTING" 0 ((4947.21007 3755.65611) (4935.89785 3755.65611) (4932.12670 3751.88495)))
("SF_PLANTING" 0 ((4932.12670 3589.74333) (4937.10170 3608.59729) (4954.75735 3630.01097) (4984.91663 3627.45057)))
("SF_PLANTING" 0 ((4935.89785 3699.09502) (4950.97998 3699.09502)))
("SF_PLANTING" 0 ((4954.75113 935.14423) (4935.89785 938.91403)))
("SF_PLANTING" 0 ((4935.89785 367.64706) (4943.43891 365.76075)))
("SF_PLANTING" 0 ((4935.89785 367.64706) (4935.89785 361.99095) (4943.43891 358.22115)))
("SF_PLANTING" 0 ((4935.89785 367.64706) (4936.05181 399.69740) (4939.82274 407.23292) (4950.97998 414.62692)
(4977.37557 414.78224)))
("SF_PLANTING" 0 ((4939.66776 3457.76799) (4950.97998 3495.47511)))
("SF_SOLAR" 0 ((4947.21007 8118.40113) (4943.43891 8133.48416)))
("SF_PLANTING" 0 ((4954.75113 3386.12342) (4943.43891 3371.04072)))
("SF_PLANTING" 0 ((4943.43891 984.16290) (4958.51538 987.03857) (4966.06335 995.47511)))
("SF_PLANTING" 0 ((4943.43891 358.22115) (4943.43891 365.76075)))
("SF_PLANTING" 0 ((4966.06335 373.30317) (4947.36403 372.10520) (4943.43891 365.76075)))
("SF_PLANTING" 0 ((4943.43891 358.22115) (4950.98688 344.34118) (4969.83450 339.36652)))
("SF_SOLAR" 0 ((4947.21007 8197.58665) (4947.21007 8190.04525)))
("SF_PLANTING" 0 ((4947.21007 3755.65611) (4958.51538 3751.73100) (4968.77783 3736.80283) (4969.98846 3702.86618)
(4984.91663 3676.47059)))
("SF_SOLAR" 0 ((4958.52229 8069.38167) (4950.97998 8088.23529)))
("SF_SOLAR" 0 ((4950.97998 8024.13281) (4950.97998 8031.67421)))
("SF_SOLAR" 0 ((4950.97998 7926.09355) (4950.97998 7914.78133)))
("SF_SOLAR" 0 ((4958.52229 7884.61538) (4950.97998 7892.15690)))
("SF_PLANTING" 0 ((4950.97998 286.57523) (4958.52229 286.57523)))
("SF_SOLAR" 0 ((4954.75113 7843.13722) (4973.60441 7843.13722)))
("SF_ARCHITECTURE" 0 ((4954.75113 5165.91210) (4973.60441 5169.68326)))
("SF_ARCHITECTURE" 0 ((4992.45894 5030.16550) (4991.25419 5022.61821) (4981.14604 5012.51674) (4962.29910 5011.46029)
(4954.75113 5015.08337)))
("SF_ARCHITECTURE" 0 ((4992.45894 5030.16550) (4966.06957 5028.96165) (4954.75113 5015.08337)))
("SF_SOLAR" 0 ((4962.29219 7948.71799) (4958.52229 7956.25939)))
("SF_MASONRY_AND_ARCH" 0 ((4958.52229 1285.82296) (4965.01391 1289.74740) (5019.90373 1376.32070) (5044.19910
1402.71493) (5091.69536 1481.90045) (5177.22432 1606.33484)))
("SF_PLANTING" 0 ((4958.52229 1138.76414) (4958.52229 1127.45192) (4962.29219 1123.67930)))
("SF_PLANTING" 0 ((4981.14672 282.80543) (4958.52229 286.57523)))
("SF_PLANTING" 0 ((4969.83450 339.36652) (4965.90871 301.66007) (4958.52229 286.57523)))
("SF_PLANTING" 0 ((4962.29219 1029.41176) (4966.06335 995.47511)))
("SF_PLANTING" 0 ((4973.60441 1048.26640) (4962.29219 1029.41176)))
("SF_PLANTING" 0 ((5037.70781 1010.55713) (5015.08337 999.39333) (4966.06335 995.47511)))
("SF_PLANTING" 0 ((4981.14672 365.76075) (4966.06335 373.30317)))
("SF_PLANTING" 0 ((4977.37557 395.92760) (4971.02523 392.00249) (4966.06335 373.30317)))
("SF_SOLAR" 0 ((4969.83450 8220.21109) (4973.60441 8227.75271)))
("SF_PLANTING" 0 ((4969.83450 3917.79830) (5003.77115 3914.02715)))
("SF_MASONRY_AND_ARCH" 0 ((4973.60441 2956.25916) (4969.83450 3016.59152) (4969.98235 3092.00577) (4973.59819
3107.08925) (4973.45656 3171.19129) (4970.13043 3182.50351) (4973.59819 3220.21143) (4969.83450 3239.06459)))
("SF_PLANTING" 0 ((5007.54106 3242.83586) (4969.83450 3239.06459)))
("SF_PLANTING" 0 ((4969.83450 1093.51527) (4985.06505 1071.03790) (5015.08269 1049.32206) (5026.39559 1048.26640)))
("SF_PLANTING" 0 ((4981.14672 365.76075) (4969.83450 339.36652)))
("SF_MASONRY_AND_ARCH" 0 ((4973.60441 2956.25916) (5007.54106 2956.25916)))
("SF_PLANTING" 0 ((4977.37557 395.92760) (4977.37557 414.78224)))
("SF_PLANTING" 0 ((4984.91663 478.88292) (4977.37557 414.78224)))
("SF_PLANTING" 0 ((4996.22885 392.15781) (4977.37557 395.92760)))
("SF_SOLAR" 0 ((4981.14672 8133.48416) (4992.45894 8118.40113)))
("SF_PLANTING" 0 ((4996.22885 392.15781) (4995.02500 377.08054) (4981.14672 365.76075)))
("SF_PLANTING" 0 ((4984.91663 241.32636) (4981.14672 282.80543)))
("SF_PLANTING" 0 ((4981.14672 282.80543) (5003.91900 316.59367) (5018.85328 324.28450)))
("SF_SOLAR" 0 ((4996.22885 8163.65000) (4984.91663 8193.81606)))
("SF_ARCHITECTURE" 0 ((4984.91663 5177.22432) (5056.56109 5192.30769)))
("SF_ARCHITECTURE" 0 ((5184.76663 4494.72138) (5070.58778 4328.80803) (5053.84038 4309.95475) (4984.91663 4200.60373)))
("SF_PLANTING" 0 ((4984.91663 3676.47059) (4984.91663 3627.45057)))
("SF_PLANTING" 0 ((4992.45894 3680.24174) (4984.91663 3676.47059)))
("SF_PLANTING" 0 ((4988.68778 3619.90950) (4984.91663 3627.45057)))
("SF_PLANTING" 0 ((4984.91663 241.32636) (5003.77115 233.93450) (5090.49774 233.94005) (5113.12217 248.86878)))
("SF_PLANTING" 0 ((5033.93665 3846.15385) (4988.68778 3846.15385)))
("SF_PLANTING" 0 ((4988.68778 3846.15385) (4992.60679 3883.86165) (5003.77115 3914.02715)))
("SF_PLANTING" 0 ((5037.70781 3616.13903) (5011.31222 3612.51629) (4988.68778 3619.90950)))
("SF_PLANTING" 0 ((4988.68778 3619.90950) (4992.45894 3589.74333)))
("SF_PLANTING" 0 ((4996.22885 3386.12342) (4985.21312 3427.59491) (4988.68778 3435.14355)))
("SF_SOLAR" 0 ((4996.22885 8080.69389) (4992.45894 8073.15226)))
("SF_SOLAR" 0 ((4992.45894 7978.88394) (4996.22885 7986.42534)))
("SF_SOLAR" 0 ((4992.45894 7948.71799) (4992.45894 7960.03020)))
("SF_ARCHITECTURE" 0 ((5365.76210 5094.26889) (5260.18100 5086.57873) (5207.39106 5075.56278) (5188.53654 5075.26652)
(5033.93665 5040.42817) (5007.54106 5030.31391) (4992.45894 5030.16550)))
("SF_PLANTING" 0 ((4992.45894 3789.59276) (5022.62443 3788.54299) (5060.33224 3766.96833)))
("SF_PLANTING" 0 ((4992.45894 3589.74333) (5011.16414 3585.81821) (5031.22217 3552.18462) (5049.02002 3544.49446)))
("SF_PLANTING" 0 ((4992.45894 3525.64129) (4988.69400 3567.11889) (4992.45894 3589.74333)))
("SF_PLANTING" 0 ((4992.45894 3525.64129) (5011.15758 3514.32217) (5019.00826 3499.24559) (5041.47771 3476.62115)))
("SF_PLANTING" 0 ((4992.45894 3525.64129) (4988.83586 3521.71538) (4988.83586 3495.47511) (4996.22885 3480.39242)))
("SF_PLANTING" 0 ((4992.45894 3318.25011) (4992.45894 3325.79186)))
("SF_SOLAR" 0 ((4996.22885 8163.65000) (5036.65113 8110.85973) (5050.07545 8084.46448) (5166.06052 7907.24638)
(5184.76663 7896.08224) (5199.84876 7899.69830)))
("SF_SOLAR" 0 ((5011.31222 8088.23529) (4996.22885 8088.23529)))
("SF_PLANTING" 0 ((4996.22885 392.15781) (5015.08337 392.15781)))
("SF_PLANTING" 0 ((5011.31222 3921.56821) (5011.31222 3917.79830) (5003.77115 3914.02715)))
("SF_PLANTING" 0 ((5011.31222 3748.11505) (5003.77115 3748.11505)))
("SF_PLANTING" 0 ((5049.02002 3239.06459) (5007.54106 3242.83586)))
("SF_MASONRY_AND_ARCH" 0 ((5007.54106 3242.83586) (5007.54106 2956.25916)))
("SF_MASONRY_AND_ARCH" 0 ((5045.24887 2960.03043) (5037.70090 2956.40690) (5007.54106 2956.25916)))
("SF_MASONRY_AND_ARCH" 0 ((5011.31222 2556.56109) (5007.54106 2571.64378)))
("SF_MASONRY_AND_ARCH" 0 ((5007.54106 2571.64378) (5018.85328 2579.18552)))
("SF_PLANTING" 0 ((5011.31222 3989.44152) (4981.15294 3995.63066) (4974.80916 3985.67093) (4982.20283 3966.81708)
(5011.31222 3936.65158)))
("SF_PLANTING" 0 ((5011.31222 3929.11052) (5011.31222 3936.65158)))
("SF_PLANTING" 0 ((5011.31222 3936.65158) (5049.02002 3978.12930)))
("SF_PLANTING" 0 ((5011.31222 3929.11052) (5015.08337 3929.11052) (5018.85328 3921.56821)))
("SF_PLANTING" 0 ((5011.31222 3929.11052) (5011.31222 3921.56821)))
("SF_PLANTING" 0 ((5018.85328 3921.56821) (5011.31222 3921.56821)))
("SF_SOLAR" 0 ((5022.62443 8171.19163) (5015.08337 8167.42081)))
("SF_SOLAR" 0 ((5015.08337 8103.31833) (5030.16550 8092.00611)))
("SF_SOLAR" 0 ((5015.08337 8103.31833) (5018.85328 8110.85973) (5022.62443 8110.85973)))
("SF_MASONRY_AND_ARCH" 0 ((5678.73303 2526.39491) (5633.48416 2526.54265) (5622.17195 2530.01154) (5603.31867
2526.40113) (5312.97093 2526.39491) (5290.34649 2530.15995) (5015.08337 2530.16618)))
("SF_PLANTING" 0 ((5015.08337 392.15781) (5015.08337 411.00962)))
("SF_PLANTING" 0 ((5015.08337 392.15781) (5030.16550 392.15781)))
("SF_PLANTING" 0 ((5015.08337 282.80543) (5026.38869 284.01029) (5032.87998 290.35271) (5037.55939 301.66007)
(5037.70781 324.28450)))
("SF_SOLAR" 0 ((5113.12217 8058.06946) (5018.85328 8197.58665)))
("SF_PLANTING" 0 ((5088.61278 3904.59989) (5075.41810 3910.10509) (5049.02002 3911.30645) (5018.85328 3921.56821)))
("SF_PLANTING" 0 ((5018.85328 3699.09502) (5037.70781 3695.32387)))
("SF_MASONRY_AND_ARCH" 0 ((5018.85328 2594.26821) (5018.85328 2579.18552)))
("SF_MASONRY_AND_ARCH" 0 ((5018.85328 2579.18552) (5041.47771 2575.42817) (5060.33224 2579.17930) (5203.61991
2579.18552)))
("SF_PLANTING" 0 ((5018.85328 1112.36708) (5026.24717 1078.43043) (5026.39559 1048.26640)))
("SF_PLANTING" 0 ((5018.85328 324.28450) (5037.70781 324.28450)))
("SF_PLANTING" 0 ((5037.70781 369.53337) (5023.82206 350.67873) (5018.85328 324.28450)))
("SF_SOLAR" 0 ((5022.62443 8076.92308) (5022.62443 8069.38167)))
("SF_SOLAR" 0 ((5026.39559 8031.67421) (5022.62443 8020.36199)))
("SF_MASONRY_AND_ARCH" 0 ((5022.62443 2477.37557) (5022.62443 2488.68778) (5026.39559 2492.45826)))
("SF_MASONRY_AND_ARCH" 0 ((5022.62443 1481.90045) (5053.84627 1534.69174) (5095.31844 1595.01640) (5119.46595
1621.56527) (5241.32771 1809.95475)))
("SF_SOLAR" 0 ((5026.39559 7978.88394) (5026.39559 7990.19615)))
("SF_SOLAR" 0 ((5026.39559 7963.80090) (5026.39559 7944.94717)))
("SF_ARCHITECTURE" 0 ((5045.24887 5735.29412) (5026.39559 5735.29412)))
("SF_ARCHITECTURE" 0 ((5026.39559 5735.29412) (5026.39559 5708.89887)))
("SF_ARCHITECTURE" 0 ((5045.24887 5708.89887) (5026.39559 5708.89887)))
("SF_MASONRY_AND_ARCH" 0 ((5682.50419 2665.91278) (5542.98643 2665.90656) (5520.36199 2662.14152) (5475.11312
2665.89966) (5441.17647 2662.14774) (5418.55204 2665.91278) (5380.84423 2662.14152) (5101.80995 2662.14774) (5067.87330
2665.90656) (5045.24887 2662.14842) (5026.39559 2665.91278)))
("SF_MASONRY_AND_ARCH" 0 ((5071.64446 2631.97613) (5026.39559 2631.97613)))
("SF_PLANTING" 0 ((5037.70781 1040.72398) (5026.39559 1048.26640)))
("SF_PLANTING" 0 ((5030.16550 4019.60826) (5040.28043 4008.29536) (5049.02002 3978.12930)))
("SF_PLANTING" 0 ((5037.70781 369.53337) (5030.16550 392.15781)))
("SF_PLANTING" 0 ((5030.16550 392.15781) (5037.71403 393.36120) (5049.02002 403.47002)))
("SF_PLANTING" 0 ((5033.93665 3872.54943) (5037.69468 3857.46606) (5033.93665 3846.15385)))
("SF_PLANTING" 0 ((5033.93665 3846.15385) (5041.48462 3839.81007) (5071.64446 3834.84163)))
("SF_PLANTING" 0 ((5067.87330 3442.68450) (5074.06244 3423.97907) (5064.10215 3418.40170) (5045.24887 3425.02919)
(5033.93665 3435.14355)))
("SF_PLANTING" 0 ((5037.70781 1040.72398) (5037.70781 1010.55713)))
("SF_PLANTING" 0 ((5037.70781 1040.72398) (5060.33224 1052.03620)))
("SF_PLANTING" 0 ((5045.24887 1010.55713) (5037.70781 1010.55713)))
("SF_PLANTING" 0 ((5037.70781 369.53337) (5056.56109 369.53337)))
("SF_PLANTING" 0 ((5037.70781 324.28450) (5052.78993 325.48167) (5067.87330 335.59672)))
("SF_ARCHITECTURE" 0 ((5041.47771 4400.45249) (5123.38462 4509.80351) (5170.73993 4585.21912) (5191.25102 4607.84355)
(5245.09762 4690.79898)))
("SF_PLANTING" 0 ((5041.47771 916.28959) (5060.33224 916.28959)))
("SF_PLANTING" 0 ((5041.47771 916.28959) (5045.24887 1010.55713)))
("SF_ARCHITECTURE" 0 ((5045.24887 5735.29412) (5060.33224 5735.29412)))
("SF_ARCHITECTURE" 0 ((5045.24887 5735.29412) (5045.24887 5708.89887)))
("SF_ARCHITECTURE" 0 ((5045.24887 5708.89887) (5060.33224 5708.89887)))
("SF_MASONRY_AND_ARCH" 0 ((5090.49774 2956.25939) (5075.41437 2956.25939) (5052.79683 2956.25939) (5045.24887
2960.03043)))
("SF_MASONRY_AND_ARCH" 0 ((5049.02002 3239.06459) (5049.01312 3144.79638) (5045.24887 3122.17195) (5049.01312
3016.59152) (5045.39695 3001.50803) (5045.24887 2960.03043)))
("SF_PLANTING" 0 ((5045.24887 1010.55713) (5075.26652 1022.92647) (5090.49774 1040.72398)))
("SF_PLANTING" 0 ((5045.24887 418.55204) (5049.02002 403.47002)))
("SF_SOLAR" 0 ((5049.02002 8031.67421) (5049.02002 8020.36199)))
("SF_PLANTING" 0 ((5075.41437 3978.12930) (5049.02002 3978.12930)))
("SF_PLANTING" 0 ((5071.64446 3589.74333) (5049.02002 3612.36776)))
("SF_PLANTING" 0 ((5094.26889 3239.06459) (5067.87330 3242.83586) (5049.02002 3239.06459)))
("SF_PLANTING" 0 ((5064.10215 399.69740) (5060.33224 403.47002) (5049.02002 403.47002)))
("SF_SOLAR" 0 ((5290.34649 8163.65011) (5260.18100 8171.03699) (5233.78541 8163.65656) (5052.78993 8163.65000)))
("SF_PLANTING" 0 ((5056.56109 369.53337) (5067.87330 335.59672)))
("SF_PLANTING" 0 ((5056.56109 369.53337) (5064.10215 399.69740)))
("SF_SOLAR" 0 ((5060.33224 7963.80090) (5060.33224 7948.71799)))
("SF_SOLAR" 0 ((5060.33224 7918.55204) (5060.33224 7929.86425)))
("SF_ARCHITECTURE" 0 ((5060.33224 5735.29412) (5086.72658 5735.29412) (5098.03880 5720.21109)))
("SF_ARCHITECTURE" 0 ((5060.33224 5735.29412) (5060.33224 5708.89887)))
("SF_ARCHITECTURE" 0 ((5060.33224 5708.89887) (5086.72658 5710.10294) (5098.03880 5720.21109)))
("SF_PLANTING" 0 ((5060.33224 3733.03167) (5056.85758 3740.57964) (5060.33224 3766.96833)))
("SF_PLANTING" 0 ((5098.03880 3778.28054) (5060.33224 3766.96833)))
("SF_PLANTING" 0 ((5060.33224 3733.03167) (5079.03088 3728.06324) (5082.95667 3721.71946)))
("SF_PLANTING" 0 ((5060.33224 3733.03167) (5064.10215 3706.63609)))
("SF_PLANTING" 0 ((5060.33224 1052.03620) (5090.49774 1048.26640)))
("SF_PLANTING" 0 ((5082.95667 1108.59729) (5061.38767 1070.89084) (5060.33224 1052.03620)))
("SF_PLANTING" 0 ((5060.33224 916.28959) (5079.18552 901.36086) (5165.91210 904.97738) (5207.39106 901.21244)
(5222.47319 904.97738)))
("SF_PLANTING" 0 ((5060.33224 916.28959) (5079.17930 933.93937) (5086.72658 935.14423)))
("SF_SOLAR" 0 ((5064.10215 8182.50385) (5064.10215 8174.96222)))
("SF_ARCHITECTURE" 0 ((5147.05882 5222.47319) (5143.13371 5216.12319) (5131.97545 5212.21143) (5109.35102 5210.10554)
(5086.72658 5199.99717) (5064.10215 5199.84876)))
("SF_PLANTING" 0 ((5064.10215 3650.07500) (5066.67568 3661.38790) (5060.34536 3691.55396) (5064.10215 3706.63609)))
("SF_PLANTING" 0 ((5082.95667 3721.71946) (5075.26652 3707.84084) (5064.10215 3706.63609)))
("SF_PLANTING" 0 ((5086.72658 422.32183) (5079.17930 407.38824) (5064.10215 399.69740)))
("SF_SOLAR" 0 ((5252.63993 8144.79638) (5237.55656 8141.03213) (5067.87330 8141.02557)))
("SF_PLANTING" 0 ((5098.03880 331.82410) (5067.87330 335.59672)))
("SF_SOLAR" 0 ((5071.64446 7990.19615) (5079.18552 7982.65452)))
("SF_PLANTING" 0 ((5105.58111 3812.21719) (5098.03258 3818.56097) (5075.56934 3824.72704) (5071.64446 3834.84163)))
("SF_PLANTING" 0 ((5088.61278 3904.59989) (5081.90000 3857.46606) (5071.64446 3834.84163)))
("SF_PLANTING" 0 ((5075.41437 3978.12930) (5079.18552 3970.58824) (5086.72658 3970.58824)))
("SF_PLANTING" 0 ((5075.41437 3978.12930) (5090.34310 4015.83710) (5095.47274 4053.53801) (5105.58111 4061.08597)))
("SF_PLANTING" 0 ((5079.18552 3518.09955) (5082.95667 3510.55781)))
("SF_PLANTING" 0 ((5086.72658 422.32183) (5079.18552 444.94627)))
("SF_PLANTING" 0 ((5116.89333 3699.09502) (5115.68857 3710.40102) (5109.34480 3716.74446) (5082.95667 3721.71946)))
("SF_MASONRY_AND_ARCH" 0 ((5082.95667 2631.97613) (5180.99548 2631.97613)))
("SF_PLANTING" 0 ((5088.61278 3904.59989) (5086.72658 3970.58824)))
("SF_PLANTING" 0 ((5124.43439 3981.90045) (5086.72658 3970.58824)))
("SF_PLANTING" 0 ((5184.76663 999.24491) (5162.14219 991.85238) (5135.74661 989.13133) (5109.35792 994.26403)
(5095.31810 969.08088) (5086.72658 935.14423)))
("SF_PLANTING" 0 ((5113.12217 938.91403) (5086.72658 935.14423)))
("SF_PLANTING" 0 ((5086.72658 524.13179) (5096.98269 501.50735) (5098.03880 478.88292)))
("SF_PLANTING" 0 ((5086.72658 422.32183) (5105.58111 422.32183)))
("SF_PLANTING" 0 ((5088.61278 3904.59989) (5101.80690 3895.33133) (5139.51776 3891.40271)))
("SF_PLANTING" 0 ((5088.61278 3904.59989) (5109.19706 3921.56821) (5120.66324 3947.96380)))
("SF_MASONRY_AND_ARCH" 0 ((5090.49774 2956.25939) (5128.20554 2956.25939)))
("SF_MASONRY_AND_ARCH" 0 ((5094.26889 3239.06459) (5094.26199 3005.27930) (5090.49774 2956.25939)))
("SF_PLANTING" 0 ((5090.49774 1040.72398) (5090.49774 1048.26640)))
("SF_PLANTING" 0 ((5101.80995 1059.57862) (5090.49774 1048.26640)))
("SF_PLANTING" 0 ((5090.49774 1040.72398) (5105.57421 1038.15758) (5112.06550 1044.50136) (5116.89333 1059.57862)))
("SF_SOLAR" 0 ((5282.80543 8099.54751) (5245.09762 8105.89129) (5214.93213 8103.32489) (5199.84876 8106.79287)
(5120.66324 8099.84367) (5094.26889 8107.08891)))
("SF_SOLAR" 0 ((5094.26889 7960.03020) (5098.03880 7952.48869)))
("SF_PLANTING" 0 ((5094.26889 3239.06459) (5128.20554 3239.06459)))
("SF_SOLAR" 0 ((5098.03880 8133.48416) (5109.35102 8118.40113)))
("SF_ARCHITECTURE" 0 ((5098.03880 5720.21109) (6331.07115 5720.21109)))
("SF_PLANTING" 0 ((5147.05882 3699.09502) (5130.92002 3733.03167) (5098.03880 3778.28054)))
("SF_PLANTING" 0 ((5105.58111 3812.21719) (5098.19378 3800.90498) (5098.03880 3778.28054)))
("SF_PLANTING" 0 ((5116.89333 1123.67930) (5098.03880 1127.45192)))
("SF_PLANTING" 0 ((5098.03880 316.74208) (5098.03880 331.82410)))
("SF_PLANTING" 0 ((5158.37104 358.22115) (5116.89333 357.01629) (5098.03880 331.82410)))
("SF_PLANTING" 0 ((5098.03880 316.74208) (5113.12217 312.97229)))
("SF_PLANTING" 0 ((5098.03880 316.74208) (5099.24355 279.03563) (5113.12217 267.72342)))
("SF_PLANTING" 0 ((5101.80995 1059.57862) (5116.89333 1059.57862)))
("SF_PLANTING" 0 ((5105.58111 1093.51527) (5101.80995 1059.57862)))
("SF_PLANTING" 0 ((5135.74661 3812.21719) (5105.58111 3812.21719)))
("SF_PLANTING" 0 ((5105.58111 422.32183) (5139.51776 399.55034) (5164.02715 377.07296) (5158.59333 369.52579)
(5158.37104 358.22115)))
("SF_PLANTING" 0 ((5105.58111 422.32183) (5113.27681 441.02805) (5124.43439 447.66176) (5135.74661 448.71889)))
("SF_SOLAR" 0 ((5203.61991 7914.78133) (5148.11482 7993.96674) (5113.12217 8058.06946)))
("SF_SOLAR" 0 ((5113.12217 8058.06946) (5316.74208 8061.84005)))
("SF_PLANTING" 0 ((5116.89333 1123.67930) (5113.12217 1112.36708)))
("SF_PLANTING" 0 ((5113.12217 267.72342) (5113.12217 248.86878)))
("SF_PLANTING" 0 ((5143.28767 290.34785) (5131.97545 285.51957) (5113.12217 267.72342)))
("SF_PLANTING" 0 ((5169.68326 245.09898) (5162.13529 241.47477) (5128.20554 241.47477) (5113.12217 248.86878)))
("SF_SOLAR" 0 ((5116.89333 7929.86425) (5116.89333 7918.55204)))
("SF_PLANTING" 0 ((5116.89333 3699.09502) (5147.05882 3699.09502)))
("SF_PLANTING" 0 ((5116.89333 3699.09502) (5113.13529 3680.24174) (5117.04729 3668.92952) (5131.97545 3655.05068)
(5154.59989 3657.61731)))
("SF_PLANTING" 0 ((5116.89333 1123.67930) (5138.31301 1142.53394) (5142.08382 1161.38439) (5139.35622 1168.02715)
(5120.66324 1165.15837)))
("SF_PLANTING" 0 ((5143.28767 1059.57862) (5116.89333 1059.57862)))
("SF_SOLAR" 0 ((5120.66324 8005.27896) (5128.20554 8005.27896)))
("SF_PLANTING" 0 ((5124.43439 3981.90045) (5124.43439 3989.44152)))
("SF_PLANTING" 0 ((5128.20554 3970.58824) (5124.43439 3981.90045)))
("SF_PLANTING" 0 ((5128.20554 3239.06459) (5165.91210 3239.06459)))
("SF_MASONRY_AND_ARCH" 0 ((5128.20554 3239.06459) (5128.20554 2956.25939)))
("SF_MASONRY_AND_ARCH" 0 ((5165.91210 2956.25939) (5150.82998 2956.25939) (5128.20554 2956.25939)))
("SF_SOLAR" 0 ((5256.40984 8088.23529) (5135.74661 8088.23529)))
("SF_SOLAR" 0 ((5135.74661 8080.69389) (5143.28767 8069.38167)))
("SF_SOLAR" 0 ((5135.74661 8039.21561) (5143.29457 8042.83846) (5177.22432 8042.98643)))
("SF_PLANTING" 0 ((5135.74661 3812.21719) (5147.20690 3797.28224) (5162.14219 3789.74084) (5207.39106 3793.51176)
(5226.24434 3800.90498)))
("SF_PLANTING" 0 ((5135.74661 3812.21719) (5144.34434 3834.83541) (5154.59989 3842.38269)))
("SF_ARCHITECTURE" 0 ((5147.05882 5222.47319) (5139.51776 5237.55656)))
("SF_ARCHITECTURE" 0 ((5207.39106 5248.86878) (5196.07817 5251.44208) (5147.06505 5244.94367) (5139.51776 5237.55656)))
("SF_PLANTING" 0 ((5154.59989 3853.69491) (5144.34434 3865.00781) (5139.51776 3891.40271)))
("SF_PLANTING" 0 ((5139.51776 3891.40271) (5162.14219 3906.48609)))
("SF_PLANTING" 0 ((5143.28767 1048.26640) (5139.51776 1033.18156)))
("SF_PLANTING" 0 ((5143.28767 1048.26640) (5143.28767 1059.57862)))
("SF_PLANTING" 0 ((5173.45441 1089.74265) (5154.74830 1078.28337) (5143.28767 1059.57862)))
("SF_PLANTING" 0 ((5192.30769 1044.49378) (5180.99548 1050.83133) (5143.28767 1048.26640)))
("SF_PLANTING" 0 ((5143.28767 290.34785) (5169.68326 260.18100)))
("SF_PLANTING" 0 ((5165.91210 324.28450) (5143.28767 290.34785)))
("SF_ARCHITECTURE" 0 ((5147.05882 5222.47319) (5184.76663 5223.52364) (5196.07817 5227.44197) (5207.39106 5237.55656)))
("SF_PLANTING" 0 ((5147.05882 3699.09502) (5157.16686 3691.55396) (5158.37104 3684.01165)))
("SF_SOLAR" 0 ((5154.59989 8005.27896) (5260.18100 7997.74423) (5275.26437 8001.50837)))
("SF_PLANTING" 0 ((5154.59989 3853.69491) (5154.59989 3842.38269)))
("SF_PLANTING" 0 ((5154.59989 3853.69491) (5168.48563 3868.77828) (5177.22432 3887.63156)))
("SF_PLANTING" 0 ((5154.59989 3842.38269) (5192.30769 3837.55645) (5214.93213 3826.24389) (5225.03982 3815.98767)
(5226.24434 3800.90498)))
("SF_PLANTING" 0 ((5154.59989 3657.61731) (5180.99548 3639.81946) (5195.92387 3639.96063) (5199.84876 3646.30509)))
("SF_PLANTING" 0 ((5154.59989 3657.61731) (5158.37104 3684.01165)))
("SF_PLANTING" 0 ((5222.47319 904.97738) (5215.82726 927.60181) (5203.61991 941.62817) (5173.45441 952.94729)
(5154.59989 953.99604)))
("SF_PLANTING" 0 ((5290.34649 516.59219) (5154.59989 516.59219)))
("SF_PLANTING" 0 ((5158.37104 3684.01165) (5199.84876 3676.47059)))
("SF_PLANTING" 0 ((5165.91210 324.28450) (5158.37104 358.22115)))
("SF_PLANTING" 0 ((5162.14219 3906.48609) (5162.14219 3917.79830)))
("SF_PLANTING" 0 ((5199.84876 3966.81708) (5195.02217 3977.97534) (5188.53032 3981.73925) (5180.99548 3980.69593)
(5169.83133 3970.58824) (5154.75486 3944.19265) (5155.79774 3925.34559) (5162.14219 3917.79830)))
("SF_PLANTING" 0 ((5180.99548 3925.33937) (5162.14219 3917.79830)))
("SF_PLANTING" 0 ((5162.14219 3906.48609) (5177.22432 3887.63156)))
("SF_SOLAR" 0 ((5165.91210 8024.13281) (5165.91210 8031.67421)))
("SF_PLANTING" 0 ((5199.84876 3235.29412) (5192.30147 3238.91686) (5165.91210 3239.06459)))
("SF_MASONRY_AND_ARCH" 0 ((5165.91210 2956.25939) (5165.91210 3239.06459)))
("SF_MASONRY_AND_ARCH" 0 ((5165.91210 2956.25939) (5199.84876 2956.25939)))
("SF_PLANTING" 0 ((5165.91210 324.28450) (5180.99548 324.13609) (5197.96380 316.74208)))
("SF_PLANTING" 0 ((5169.68326 245.09898) (5169.68326 260.18100)))
("SF_PLANTING" 0 ((5196.07885 279.03563) (5169.68326 260.18100)))
("SF_PLANTING" 0 ((5169.68326 245.09898) (5180.99548 237.71120) (5211.16097 237.55656)))
("SF_PLANTING" 0 ((5177.22432 3887.63156) (5226.24434 3891.40271) (5256.40984 3887.63156)))
("SF_PLANTING" 0 ((5180.99548 3925.33937) (5203.61991 3922.62489) (5263.95215 3951.73495)))
("SF_PLANTING" 0 ((5180.99548 3925.33937) (5185.81618 3944.19265) (5199.84876 3966.81708)))
("SF_SOLAR" 0 ((5184.76663 8069.38167) (5184.76663 8080.69389)))
("SF_SOLAR" 0 ((5184.76663 7963.80090) (5203.61991 7971.19423) (5380.84423 7971.34231)))
("SF_SOLAR" 0 ((5192.30769 7865.76165) (5184.76663 7884.61538)))
("SF_PLANTING" 0 ((5184.76663 999.24491) (5207.39106 988.08801) (5241.32771 984.16290)))
("SF_PLANTING" 0 ((5192.30769 1044.49378) (5184.76663 999.24491)))
("SF_SOLAR" 0 ((5324.28314 8042.98643) (5297.88880 8039.21561) (5192.30769 8042.98643)))
("SF_PLANTING" 0 ((5214.93213 1052.03620) (5192.30769 1044.49378)))
("SF_SOLAR" 0 ((5199.84876 7978.88394) (5196.07885 7986.42534)))
("SF_PLANTING" 0 ((5196.07885 279.03563) (5211.16097 267.72342)))
("SF_PLANTING" 0 ((5196.07885 279.03563) (5197.96380 316.74208)))
("SF_PLANTING" 0 ((5197.96380 316.74208) (5215.08676 350.67251) (5248.86878 377.07296)))
("SF_PLANTING" 0 ((5256.40984 343.13631) (5245.09140 325.48167) (5214.93213 316.88982) (5197.96380 316.74208)))
("SF_SOLAR" 0 ((5199.84876 7899.69830) (5199.84876 7907.23982)))
("SF_SOLAR" 0 ((5199.84876 7899.69830) (5207.39106 7895.92760)))
("SF_PLANTING" 0 ((5226.24434 3974.35939) (5199.84876 3966.81708)))
("SF_PLANTING" 0 ((5207.39106 3676.47059) (5199.84876 3676.47059)))
("SF_PLANTING" 0 ((5199.84876 3646.30509) (5199.84876 3676.47059)))
("SF_PLANTING" 0 ((5207.39106 3676.47059) (5222.38337 3671.50871) (5225.87568 3666.20124) (5214.92590 3651.13167)
(5199.84876 3646.30509)))
("SF_MASONRY_AND_ARCH" 0 ((5199.84876 2956.25939) (5199.84876 3235.29412)))
("SF_PLANTING" 0 ((5233.78541 3239.06459) (5207.39729 3238.91686) (5199.84876 3235.29412)))
("SF_MASONRY_AND_ARCH" 0 ((5199.84876 2956.25939) (5230.01550 2956.25939)))
("SF_SOLAR" 0 ((5203.61991 8118.40113) (5207.39106 8125.94276)))
("SF_SOLAR" 0 ((5214.93213 7843.13722) (5203.61991 7843.13722)))
("SF_SOLAR" 0 ((5207.39106 8016.59118) (5207.39106 8031.67421)))
("SF_SOLAR" 0 ((5403.46867 7941.17647) (5392.15645 7937.41233) (5237.55656 7937.41233) (5218.70328 7941.16335)
(5207.39106 7937.40577)))
("SF_ARCHITECTURE" 0 ((5207.39106 5248.86878) (5207.39106 5237.55656)))
("SF_ARCHITECTURE" 0 ((5207.39106 5248.86878) (5214.93835 5255.21256) (5275.26369 5263.65566) (5286.57658 5260.18100)))
("SF_ARCHITECTURE" 0 ((5290.34649 5241.32771) (5248.86878 5233.93382) (5218.70328 5233.93382) (5207.39106 5237.55656)))
("SF_PLANTING" 0 ((5207.39106 3676.47059) (5211.30939 3714.17839) (5219.90057 3748.10814) (5226.25057 3754.45848)
(5248.86878 3759.42726)))
("SF_MASONRY_AND_ARCH" 0 ((5663.64966 2631.97613) (5644.79638 2635.74661) (5501.50871 2635.74038) (5482.65419
2631.98303) (5460.02975 2635.74038) (5305.42986 2635.74038) (5290.34649 2632.12387) (5207.39106 2631.97613)))
("SF_PLANTING" 0 ((5211.16097 267.72342) (5211.16097 237.55656)))
("SF_PLANTING" 0 ((5256.40984 282.80543) (5211.16097 267.72342)))
("SF_PLANTING" 0 ((5263.95215 237.55656) (5248.86878 233.78676) (5211.16097 237.55656)))
("SF_SOLAR" 0 ((5214.93213 7960.03020) (5218.70328 7948.71799)))
("SF_SOLAR" 0 ((5463.80090 7843.13722) (5256.40984 7843.28529) (5234.84208 7858.22025) (5214.93213 7899.69830)))
("SF_PLANTING" 0 ((5214.93213 1093.51527) (5222.47319 1092.31041) (5230.01550 1082.20305)))
("SF_SOLAR" 0 ((5222.47319 8080.69389) (5230.01550 8069.38167)))
("SF_SOLAR" 0 ((5448.71753 7895.92760) (5433.63541 7899.69174) (5222.47319 7903.46912)))
("SF_PLANTING" 0 ((5271.49321 4023.37817) (5263.94525 4029.57455) (5248.86878 4026.09955) (5222.47319 4004.52489)))
("SF_PLANTING" 0 ((5275.26437 912.51980) (5263.95147 905.13201) (5222.47319 904.97738)))
("SF_PLANTING" 0 ((5226.24434 3865.00713) (5248.86878 3857.46606)))
("SF_PLANTING" 0 ((5248.86878 3789.59276) (5226.24434 3800.90498)))
("SF_SOLAR" 0 ((5233.78541 8114.63054) (5230.01550 8133.48416)))
("SF_SOLAR" 0 ((5230.01550 8031.67421) (5230.01550 8020.36199)))
("SF_MASONRY_AND_ARCH" 0 ((5230.01550 2956.25939) (5263.95215 2956.25939)))
("SF_MASONRY_AND_ARCH" 0 ((5233.78541 3239.06459) (5233.77919 2997.73756) (5230.01550 2956.25939)))
("SF_SOLAR" 0 ((5233.78541 7922.32274) (5233.78541 7929.86425)))
("SF_PLANTING" 0 ((5233.78541 3239.06459) (5260.17477 3238.91686) (5267.72206 3235.29412)))
("SF_PLANTING" 0 ((5241.32771 984.16290) (5290.34649 984.16290)))
("SF_PLANTING" 0 ((5241.32771 984.16290) (5242.38314 1025.64197) (5249.92545 1040.57557) (5260.18100 1047.06086)
(5282.80543 1039.52602) (5301.50475 1021.86934) (5309.20102 995.47511)))
("SF_SOLAR" 0 ((5252.63993 8182.50385) (5245.09762 8197.58665)))
("SF_SOLAR" 0 ((5252.63993 8144.79638) (5248.86878 8159.87941)))
("SF_PLANTING" 0 ((5252.63993 3849.92500) (5248.86878 3857.46606)))
("SF_PLANTING" 0 ((5248.86878 3857.46606) (5256.40984 3887.63156)))
("SF_PLANTING" 0 ((5248.86878 3789.59276) (5248.86878 3759.42726)))
("SF_PLANTING" 0 ((5248.86878 3789.59276) (5286.57658 3797.13382)))
("SF_PLANTING" 0 ((5248.86878 3759.42726) (5271.49321 3743.44876) (5294.11765 3737.09876) (5335.59536 3744.34389)))
("SF_PLANTING" 0 ((5248.86878 3717.94830) (5263.95215 3713.12172) (5305.42986 3680.24174)))
("SF_PLANTING" 0 ((5305.42986 373.30317) (5294.11765 363.04729) (5279.03428 362.14559) (5248.86878 377.07296)))
("SF_PLANTING" 0 ((5248.86878 377.07296) (5252.63993 388.38518)))
("SF_SOLAR" 0 ((5252.63993 8144.79638) (5267.71584 8137.10679) (5311.91550 8076.92308) (5316.74208 8061.84005)))
("SF_SOLAR" 0 ((5252.63993 8080.69389) (5252.63993 8069.38167)))
("SF_SOLAR" 0 ((5252.63993 8027.90339) (5252.63993 8020.36199)))
("SF_SOLAR" 0 ((5252.63993 8009.04977) (5260.18722 8012.67251) (5324.28314 8012.96855) (5343.13767 8016.59118)))
("SF_SOLAR" 0 ((5252.63993 7990.19615) (5252.63993 7978.88394)))
("SF_SOLAR" 0 ((5252.63993 7948.71799) (5252.63993 7960.03020)))
("SF_PLANTING" 0 ((5373.30317 3800.90498) (5361.84287 3823.52941) (5316.74208 3863.95758) (5290.34649 3879.03450)
(5256.40984 3887.63156)))
("SF_PLANTING" 0 ((5263.95215 237.55656) (5267.57421 260.18100) (5256.40984 282.80543)))
("SF_PLANTING" 0 ((5297.88880 309.19966) (5271.49321 304.37353) (5257.61459 290.35271) (5256.40984 282.80543)))
("SF_MASONRY_AND_ARCH" 0 ((5263.95215 2956.25939) (5312.97093 2956.25939)))
("SF_MASONRY_AND_ARCH" 0 ((5271.49321 3005.27930) (5264.10000 2993.96708) (5263.95215 2956.25939)))
("SF_PLANTING" 0 ((5263.95215 237.55656) (5275.26437 233.79163) (5377.07432 233.78676)))
("SF_MASONRY_AND_ARCH" 0 ((5271.49321 3005.27930) (5271.48699 3193.81572) (5267.72206 3235.29412)))
("SF_PLANTING" 0 ((5312.97093 3239.06459) (5279.03495 3238.91686) (5267.72206 3235.29412)))
("SF_PLANTING" 0 ((5286.57658 3797.13382) (5285.37183 3823.52319) (5271.49321 3831.07048)))
("SF_MASONRY_AND_ARCH" 0 ((5282.80543 2997.73756) (5271.49321 3005.27930)))
("SF_SOLAR" 0 ((5275.26437 8069.38167) (5275.26437 8084.46448)))
("SF_SOLAR" 0 ((5275.26437 8031.67421) (5275.26437 8020.36199)))
("SF_SOLAR" 0 ((5275.26437 7978.88394) (5275.26437 7990.19615)))
("SF_SOLAR" 0 ((5275.26437 7926.09355) (5275.26437 7914.78133)))
("SF_PLANTING" 0 ((5275.26437 912.51980) (5282.80543 912.51980)))
("SF_PLANTING" 0 ((5275.26437 912.51980) (5271.64129 927.60181) (5290.34649 976.62048)))
("SF_PLANTING" 0 ((5279.03428 3917.79830) (5305.43609 3943.13654) (5324.28314 3947.81572) (5342.98925 3940.26776)
(5353.25170 3925.33937) (5354.44989 3914.02715)))
("SF_PLANTING" 0 ((5282.80543 912.51980) (5286.73054 906.02681) (5297.88880 901.35532) (5331.82477 901.36086)
(5343.13767 908.74717)))
("SF_PLANTING" 0 ((5297.88880 935.14423) (5282.80543 912.51980)))
("SF_ARCHITECTURE" 0 ((5290.34649 5241.32771) (5286.57658 5260.18100)))
("SF_ARCHITECTURE" 0 ((5286.57658 5260.18100) (5297.88880 5267.56810) (5358.21980 5267.87048) (5373.30317 5271.48699)
(5414.77466 5271.33857) (5422.32319 5263.95215)))
("SF_PLANTING" 0 ((5324.28314 3793.36391) (5286.57658 3797.13382)))
("SF_SOLAR" 0 ((5550.52749 8163.65011) (5527.90305 8163.65011) (5301.65939 8163.65011) (5290.34649 8163.65011)))
("SF_SOLAR" 0 ((5354.44989 8065.61086) (5330.76878 8107.08891) (5290.34649 8163.65011)))
("SF_SOLAR" 0 ((5290.34649 8125.94276) (5297.88880 8133.48416)))
("SF_ARCHITECTURE" 0 ((5290.34649 5241.32771) (5301.65939 5244.94977) (5380.84423 5245.24604) (5407.23982 5249.02342)
(5414.77466 5252.79389) (5422.32319 5263.95215)))
("SF_MASONRY_AND_ARCH" 0 ((5369.53201 2220.96505) (5301.65939 2213.57873) (5290.34649 2224.73631)))
("SF_MASONRY_AND_ARCH" 0 ((5369.53201 2239.81900) (5301.65939 2235.89389) (5290.34649 2224.73631)))
("SF_PLANTING" 0 ((5290.34649 1097.28507) (5298.03665 1083.25181) (5320.51324 1070.13688) (5346.90758 1078.43043)))
("SF_PLANTING" 0 ((5290.34649 984.16290) (5290.34649 976.62048)))
("SF_PLANTING" 0 ((5290.34649 984.16290) (5309.20102 995.47511)))
("SF_PLANTING" 0 ((5290.34649 976.62048) (5312.97093 970.28428) (5324.28314 976.62048)))
("SF_SOLAR" 0 ((5294.11765 7948.71799) (5294.11765 7960.03020)))
("SF_PLANTING" 0 ((5294.11765 335.59672) (5294.11765 331.82410) (5301.65871 328.05430)))
("SF_SOLAR" 0 ((5297.88880 7997.73756) (5331.82477 7997.58959) (5343.13767 7993.96674)))
("SF_SOLAR" 0 ((5297.88880 7978.88394) (5297.88880 7990.19615)))
("SF_SOLAR" 0 ((5297.88880 7914.78133) (5297.88880 7926.09355)))
("SF_PLANTING" 0 ((5297.88880 309.19966) (5339.36652 280.22590) (5377.07432 267.72342)))
("SF_PLANTING" 0 ((5297.88880 309.19966) (5301.65871 328.05430)))
("SF_PLANTING" 0 ((5331.82545 343.13631) (5301.65871 328.05430)))
("SF_SOLAR" 0 ((5305.42986 8031.67421) (5305.42986 8024.13281)))
("SF_PLANTING" 0 ((5305.42986 3680.24174) (5309.20102 3642.53394)))
("SF_PLANTING" 0 ((5324.28314 3699.09502) (5305.42986 3680.24174)))
("SF_SOLAR" 0 ((5316.74208 8107.08891) (5309.20102 8099.54751)))
("SF_PLANTING" 0 ((5309.20102 995.47511) (5319.45656 987.78563) (5324.28314 976.62048)))
("SF_PLANTING" 0 ((5335.59536 3898.94378) (5312.97093 3917.79830)))
("SF_PLANTING" 0 ((5343.13767 3239.06459) (5312.97093 3239.06459)))
("SF_MASONRY_AND_ARCH" 0 ((5312.97093 3239.06459) (5316.74208 3178.73303) (5312.97093 2956.25939)))
("SF_MASONRY_AND_ARCH" 0 ((5343.13767 2956.25939) (5312.97093 2956.25939)))
("SF_PLANTING" 0 ((5320.51324 388.38518) (5298.04276 396.98394) (5294.42036 403.47489) (5302.71538 425.79061)
(5312.97093 426.09446)))
("SF_SOLAR" 0 ((5516.59084 8144.79638) (5501.50871 8141.03213) (5316.74208 8141.02557)))
("SF_SOLAR" 0 ((5316.74208 8061.84005) (5324.14219 8057.91471) (5368.48281 7997.73756) (5380.84423 7971.34231)))
("SF_PLANTING" 0 ((5320.51324 388.38518) (5316.74208 380.84559)))
("SF_SOLAR" 0 ((5320.51324 7978.88394) (5320.51324 7990.19615)))
("SF_SOLAR" 0 ((5320.51324 7960.03020) (5320.51324 7948.71799)))
("SF_PLANTING" 0 ((5320.51324 388.38518) (5343.13767 392.15781)))
("SF_PLANTING" 0 ((5324.28314 3793.36391) (5335.59536 3744.34389)))
("SF_PLANTING" 0 ((5324.28314 3793.36391) (5339.36652 3800.75690) (5373.30317 3800.90498)))
("SF_PLANTING" 0 ((5388.38654 970.96437) (5354.44989 969.22794) (5324.28314 976.62048)))
("SF_PLANTING" 0 ((5358.21980 1003.01753) (5335.75034 1025.64197) (5331.82545 1036.95419)))
("SF_PLANTING" 0 ((5356.33484 320.51188) (5335.75034 329.10373) (5331.82545 343.13631)))
("SF_PLANTING" 0 ((5331.82545 343.13631) (5339.37274 349.48077) (5350.67873 350.67873)))
("SF_SOLAR" 0 ((5354.44989 8065.61086) (5346.90136 8060.31674) (5335.59536 8061.84005)))
("SF_PLANTING" 0 ((5395.92760 3861.23722) (5373.30317 3866.19876) (5335.59536 3898.94378)))
("SF_PLANTING" 0 ((5335.59536 3898.94378) (5354.44989 3914.02715)))
("SF_PLANTING" 0 ((5411.01097 3748.11505) (5384.61538 3740.72115) (5346.90826 3740.72115) (5335.59536 3744.34389)))
("SF_PLANTING" 0 ((5343.13767 908.74717) (5335.59536 931.37161)))
("SF_PLANTING" 0 ((5339.36652 414.78224) (5343.13767 392.15781)))
("SF_SOLAR" 0 ((5343.13767 8103.31833) (5369.53201 8099.70204) (5380.84423 8103.17025) (5531.97692 8107.38507)
(5546.75758 8095.77670)))
("SF_SOLAR" 0 ((5343.13767 7978.88394) (5343.13767 7993.96674)))
("SF_SOLAR" 0 ((5358.21980 7997.73756) (5343.13767 7993.96674)))
("SF_PLANTING" 0 ((5343.13767 3665.15837) (5346.90758 3650.07500)))
("SF_PLANTING" 0 ((5343.13767 3585.97285) (5349.33303 3589.89796) (5346.90758 3601.05554)))
("SF_PLANTING" 0 ((5343.13767 3239.06459) (5399.69186 3238.91686) (5407.23982 3235.29412)))
("SF_MASONRY_AND_ARCH" 0 ((5343.13767 3239.06459) (5343.28552 3178.73303) (5346.90758 3159.87907) (5343.13767
2956.25939)))
("SF_MASONRY_AND_ARCH" 0 ((5403.46867 2967.57138) (5388.38654 2956.25939) (5343.13767 2956.25939)))
("SF_PLANTING" 0 ((5343.13767 908.74717) (5365.76210 908.74717)))
("SF_PLANTING" 0 ((5343.13767 392.15781) (5357.02251 380.84559) (5361.99095 365.76075)))
("SF_PLANTING" 0 ((5361.99095 1055.80600) (5346.90758 1078.43043)))
("SF_PLANTING" 0 ((5350.67873 1089.74265) (5346.90758 1078.43043)))
("SF_PLANTING" 0 ((5399.69876 407.23982) (5366.81821 429.87048) (5360.93428 456.25848) (5350.67873 475.11312)))
("SF_PLANTING" 0 ((5365.76210 329.94061) (5350.67873 350.67873)))
("SF_PLANTING" 0 ((5350.67873 350.67873) (5361.99095 365.76075)))
("SF_SOLAR" 0 ((5354.44989 8065.61086) (5365.76210 8058.06946)))
("SF_PLANTING" 0 ((5369.53201 3910.25600) (5354.44989 3914.02715)))
("SF_PLANTING" 0 ((5365.76210 329.94061) (5361.99095 320.51188) (5356.33484 320.51188)))
("SF_PLANTING" 0 ((5356.33484 320.51188) (5384.61538 275.26301)))
("SF_PLANTING" 0 ((5365.76210 329.94061) (5356.33484 320.51188)))
("SF_SOLAR" 0 ((5358.21980 8114.63054) (5361.99095 8125.94276)))
("SF_SOLAR" 0 ((5358.21980 8027.90339) (5365.76210 8039.21561)))
("SF_SOLAR" 0 ((5361.99095 7948.71799) (5361.99095 7960.03020)))
("SF_PLANTING" 0 ((5388.38654 328.05430) (5383.41776 350.67251) (5361.99095 365.76075)))
("SF_SOLAR" 0 ((5667.42081 7941.17647) (5656.10860 7937.41233) (5452.48869 7938.61007) (5437.55373 7952.48869)
(5404.52500 7997.73756) (5365.76210 8058.06946)))
("SF_SOLAR" 0 ((5569.38201 8061.84005) (5414.78088 8061.83348) (5395.92760 8058.08258) (5377.07432 8061.68552)
(5365.76210 8058.06946)))
("SF_ARCHITECTURE" 0 ((5365.76210 5094.26889) (5399.69876 5067.87330)))
("SF_ARCHITECTURE" 0 ((5365.76210 5094.26889) (5380.84423 5105.42613) (5403.31471 5101.65532) (5407.08518 5079.18552)
(5399.69876 5067.87330)))
("SF_PLANTING" 0 ((5365.76210 927.60181) (5365.76210 908.74717)))
("SF_PLANTING" 0 ((5388.38654 908.74717) (5365.76210 908.74717)))
("SF_PLANTING" 0 ((5365.76210 329.94061) (5388.38654 328.05430)))
("SF_MASONRY_AND_ARCH" 0 ((5399.69876 2202.11188) (5411.01052 2217.19457) (5407.08518 2235.89389) (5399.69808
2239.66437) (5369.53201 2239.81900)))
("SF_MASONRY_AND_ARCH" 0 ((5369.53201 2220.96505) (5369.53201 2239.81900)))
("SF_MASONRY_AND_ARCH" 0 ((5369.53201 2220.96505) (5388.38609 2212.36765) (5399.69876 2202.11188)))
("SF_PLANTING" 0 ((5399.69876 3800.90498) (5373.30317 3800.90498)))
("SF_PLANTING" 0 ((5377.07432 233.78676) (5377.07432 267.72342)))
("SF_PLANTING" 0 ((5384.61538 275.26301) (5377.07432 267.72342)))
("SF_PLANTING" 0 ((5377.07432 233.78676) (5414.78088 233.94005) (5437.40532 248.86878)))
("SF_SOLAR" 0 ((5380.84423 8080.69389) (5388.38654 8069.38167)))
("SF_SOLAR" 0 ((5403.46867 7941.17647) (5394.87783 7960.03009) (5380.84423 7971.34231)))
("SF_SOLAR" 0 ((5388.38654 7914.78133) (5384.61538 7926.09355)))
("SF_PLANTING" 0 ((5384.61538 3902.71493) (5403.46867 3898.94378)))
("SF_PLANTING" 0 ((5399.69876 275.26301) (5384.61538 275.26301)))
("SF_SOLAR" 0 ((5388.38654 8114.63054) (5388.38654 8133.48416)))
("SF_SOLAR" 0 ((5584.46414 8042.98643) (5550.52749 8039.21561) (5422.32319 8039.22217) (5388.38654 8042.98643)))
("SF_PLANTING" 0 ((5388.38654 1025.64197) (5411.01097 1025.64197)))
("SF_PLANTING" 0 ((5388.38654 1025.64197) (5392.15645 999.24491)))
("SF_PLANTING" 0 ((5388.38654 1025.64197) (5392.31143 1059.57104) (5399.69876 1067.11821)))
("SF_PLANTING" 0 ((5411.01097 969.08088) (5388.38654 970.96437)))
("SF_PLANTING" 0 ((5388.38654 908.74717) (5392.15645 927.60181) (5388.38654 970.96437)))
("SF_PLANTING" 0 ((5388.38654 970.96437) (5392.15645 999.24491)))
("SF_PLANTING" 0 ((5448.71753 908.74717) (5426.09310 901.20758) (5395.93382 901.36086) (5388.38654 908.74717)))
("SF_PLANTING" 0 ((5388.38654 328.05430) (5411.01097 320.51188)))
("SF_PLANTING" 0 ((5392.15645 999.24491) (5411.01097 999.24491)))
("SF_PLANTING" 0 ((5414.78088 3831.07048) (5404.66652 3838.61900) (5395.92760 3861.23722)))
("SF_PLANTING" 0 ((5395.92760 3861.23722) (5407.23982 3868.77828)))
("SF_PLANTING" 0 ((5399.69876 5067.87330) (5399.70498 3985.67161) (5403.32081 3970.58824) (5399.85271 3940.42274)
(5403.46867 3898.94378)))
("SF_PLANTING" 0 ((5411.01097 3748.11505) (5399.84661 3782.05170) (5399.69876 3800.90498)))
("SF_PLANTING" 0 ((5399.69876 3800.90498) (5422.32319 3812.21719)))
("SF_MASONRY_AND_ARCH" 0 ((5399.69876 2202.11188) (5399.69876 1067.11821)))
("SF_PLANTING" 0 ((5418.55204 1048.26640) (5399.69876 1067.11821)))
("SF_PLANTING" 0 ((5399.69876 407.23982) (5399.69876 377.07296)))
("SF_PLANTING" 0 ((5399.69876 407.23982) (5433.63541 414.78224)))
("SF_PLANTING" 0 ((5437.40532 256.41120) (5418.55204 270.28835) (5399.69876 275.26301)))
("SF_PLANTING" 0 ((5399.69876 275.26301) (5403.46867 305.42986)))
("SF_SOLAR" 0 ((5403.46867 7941.17647) (5426.09310 7914.78133)))
("SF_PLANTING" 0 ((5403.46867 3898.94378) (5407.23982 3868.77828)))
("SF_MASONRY_AND_ARCH" 0 ((5456.25984 2956.25939) (5418.55204 2956.25939) (5403.46867 2967.57138)))
("SF_MASONRY_AND_ARCH" 0 ((5403.46867 2967.57138) (5403.47557 3182.50351) (5407.23982 3235.29412)))
("SF_PLANTING" 0 ((5411.01097 312.97229) (5407.23982 312.97229) (5403.46867 305.42986)))
("SF_PLANTING" 0 ((5411.01097 312.97229) (5411.01097 309.19966) (5403.46867 305.42986)))
("SF_SOLAR" 0 ((5539.21527 8009.04977) (5520.36199 8012.81403) (5407.23982 8012.82059)))
("SF_PLANTING" 0 ((5422.32319 3857.46606) (5407.23982 3868.77828)))
("SF_PLANTING" 0 ((5456.25984 3239.06459) (5426.09310 3242.68812) (5407.23982 3235.29412)))
("SF_PLANTING" 0 ((5407.23982 516.59219) (5509.04977 516.59219)))
("SF_SOLAR" 0 ((5411.01097 8133.48416) (5411.01097 8125.94276)))
("SF_PLANTING" 0 ((5411.01097 3748.11505) (5554.29864 3748.12127) (5576.92308 3751.88495)))
("SF_PLANTING" 0 ((5411.01097 3695.32432) (5422.32319 3695.32432) (5697.58631 3695.32432) (5708.89853 3695.32432)))
("SF_PLANTING" 0 ((5411.01097 1025.64197) (5411.01097 999.24491)))
("SF_PLANTING" 0 ((5418.55204 1048.26640) (5411.01097 1025.64197)))
("SF_PLANTING" 0 ((5411.01097 969.08088) (5411.01097 999.24491)))
("SF_PLANTING" 0 ((5448.71753 923.83201) (5422.47104 946.45645) (5411.01097 969.08088)))
("SF_PLANTING" 0 ((5411.01097 312.97229) (5411.01097 320.51188)))
("SF_PLANTING" 0 ((5433.63541 324.28450) (5411.01097 320.51188)))
("SF_PLANTING" 0 ((5414.78088 3831.07048) (5415.97873 3819.76516) (5422.32319 3812.21719)))
("SF_PLANTING" 0 ((5414.78088 3831.07048) (5421.12534 3838.61900) (5422.32319 3857.46606)))
("SF_PLANTING" 0 ((5418.55204 1048.26640) (5452.48869 1048.26640)))
("SF_SOLAR" 0 ((5433.63541 7937.40577) (5422.32319 7937.40577)))
("SF_ARCHITECTURE" 0 ((5460.02975 5263.95215) (5422.32319 5263.95215)))
("SF_PLANTING" 0 ((5422.32319 3857.46606) (5456.25984 3853.69491)))
("SF_PLANTING" 0 ((5444.94762 3812.21719) (5422.32319 3812.21719)))
("SF_SOLAR" 0 ((5429.86425 8031.67421) (5426.09310 8024.13281)))
("SF_SOLAR" 0 ((5433.63541 8114.63054) (5437.40532 8125.94276)))
("SF_SOLAR" 0 ((5433.63541 8069.38167) (5433.63541 8080.69389)))
("SF_PLANTING" 0 ((5433.63541 444.94627) (5437.10939 433.63405) (5433.63541 414.78224)))
("SF_PLANTING" 0 ((5433.63541 414.78224) (5433.48699 361.99095) (5429.87048 346.90894) (5433.63541 324.28450)))
("SF_PLANTING" 0 ((5433.63541 324.28450) (5441.17647 320.51188)))
("SF_SOLAR" 0 ((5437.40532 8088.23529) (5527.89683 8088.38326) (5535.44536 8092.00611)))
("SF_SOLAR" 0 ((5437.40532 8001.50837) (5444.95385 7997.88552) (5512.82093 7997.73767) (5550.52749 8004.08133)
(5584.46414 8001.66290) (5603.31867 8012.82059)))
("SF_SOLAR" 0 ((5633.48416 7975.11312) (5622.17195 7971.34887) (5437.40532 7971.34231)))
("SF_PLANTING" 0 ((5437.40532 256.41120) (5437.40532 248.86878)))
("SF_PLANTING" 0 ((5437.40532 256.41120) (5441.17647 320.51188)))
("SF_PLANTING" 0 ((5460.02975 248.86878) (5437.40532 248.86878)))
("SF_PLANTING" 0 ((5486.42534 324.28450) (5441.17647 320.51188)))
("SF_PLANTING" 0 ((5509.04977 3804.67613) (5493.96640 3797.28224) (5460.02975 3797.28880) (5452.49491 3801.05962)
(5444.94762 3812.21719)))
("SF_PLANTING" 0 ((5444.94762 3812.21719) (5452.34061 3827.30057) (5456.25984 3853.69491)))
("SF_SOLAR" 0 ((5448.71753 7929.86425) (5460.02975 7914.78133)))
("SF_SOLAR" 0 ((5448.71753 7895.92760) (5486.42534 7850.67873)))
("SF_SOLAR" 0 ((5448.71753 7895.92760) (5467.57206 7903.46256) (5535.44536 7899.69830) (5558.06980 7903.46256)
(5693.81640 7903.46912)))
("SF_PLANTING" 0 ((5448.71753 923.83201) (5448.71753 908.74717)))
("SF_PLANTING" 0 ((5448.71753 923.83201) (5458.82590 935.14423) (5460.02975 950.22624)))
("SF_PLANTING" 0 ((5516.59084 916.28959) (5501.50803 901.36086) (5463.80090 901.36086) (5448.71753 908.74717)))
("SF_SOLAR" 0 ((5456.25984 8114.63054) (5452.48869 8133.48416)))
("SF_PLANTING" 0 ((5456.25984 1006.78733) (5452.48869 1048.26640)))
("SF_MASONRY_AND_ARCH" 0 ((5452.48869 1048.26640) (5452.63676 1112.36708) (5456.25294 1127.45192) (5456.25294
1613.87726) (5452.48869 1636.50170) (5452.49491 2062.59400) (5456.25294 2115.38462) (5452.63676 2130.46731) (5452.48869
2194.57014) (5456.25294 2217.19457) (5456.25984 2307.69231)))
("SF_PLANTING" 0 ((5509.04977 1052.03620) (5467.57206 1051.88846) (5452.48869 1048.26640)))
("SF_PLANTING" 0 ((5456.25939 3868.77828) (5460.02975 3857.46606) (5456.25984 3853.69491)))
("SF_ARCHITECTURE" 0 ((5456.25939 3868.77828) (5456.25939 3876.32624) (5456.25939 3996.98382) (5456.25939 4015.83710)
(5456.25939 4095.02262) (5456.25939 4117.64706) (5456.25939 4524.88688) (5456.25939 4547.51131) (5456.25939 4788.83903)
(5456.25939 4803.92115) (5456.25939 4822.77568) (5456.25939 4939.66776) (5456.25939 4954.75113) (5456.25939 5030.16550)
(5456.25939 5067.87330) (5456.25939 5082.95667) (5456.25984 5158.37104)))
("SF_PLANTING" 0 ((5456.25939 3868.77828) (5514.70588 3897.05882)))
("SF_SOLAR" 0 ((5456.25984 8069.38167) (5456.25984 8080.69389)))
("SF_SOLAR" 0 ((5456.25984 8020.36199) (5456.25984 8031.67421)))
("SF_ARCHITECTURE" 0 ((5456.25984 5158.37104) (5622.17195 5150.68156) (5795.62568 5124.28631) (5984.16290 5074.35894)
(6052.03620 5051.73450) (6127.45124 5021.57466) (6157.61686 5007.38710) (6157.61686 4984.91663) (6157.61686 4132.73043)
(6157.61686 4117.64706) (6157.61686 4068.62704) (6157.61686 4027.14932)))
("SF_MASONRY_AND_ARCH" 0 ((5456.25984 2956.25939) (5456.40769 3024.13247) (5460.02975 3042.98643) (5460.02353
3182.50351) (5456.40769 3197.58699) (5456.25984 3239.06459)))
("SF_PLANTING" 0 ((5456.25984 3239.06459) (5497.73756 3242.68812) (5512.82025 3237.86674) (5524.13314 3227.75238)))
("SF_MASONRY_AND_ARCH" 0 ((5456.25984 2956.25939) (5478.88428 2956.25939) (5505.27240 2956.25939) (5512.82093
2956.25939)))
("SF_MASONRY_AND_ARCH" 0 ((6248.11459 2149.32127) (6229.26120 2150.37070) (6127.45124 2189.60170) (6010.55781
2227.45735) (5848.41629 2269.83665) (5723.98190 2292.46188) (5659.87975 2296.52783) (5618.40079 2303.77410) (5456.25984
2307.69231)))
("SF_PLANTING" 0 ((5456.25984 1006.78733) (5509.04977 1006.78733)))
("SF_PLANTING" 0 ((5456.25984 1006.78733) (5452.64333 984.16290) (5460.02975 950.22624)))
("SF_ARCHITECTURE" 0 ((5460.02975 5263.95215) (5478.88428 5249.02342) (5542.98643 5245.09762) (5607.08857 5245.24604)
(5618.40079 5248.86878)))
("SF_ARCHITECTURE" 0 ((5618.40079 5260.18100) (5607.08857 5267.56810) (5561.83971 5267.87048) (5546.75758 5271.48699)
(5471.34265 5271.33857) (5460.02975 5263.95215)))
("SF_PLANTING" 0 ((5482.65419 950.22624) (5460.02975 950.22624)))
("SF_PLANTING" 0 ((5524.13314 237.55656) (5516.58462 233.93382) (5482.65419 233.93450) (5460.02975 248.86878)))
("SF_PLANTING" 0 ((5475.11312 267.72342) (5460.02975 248.86878)))
("SF_PLANTING" 0 ((5463.80090 392.15781) (5476.16290 358.22115) (5486.42534 343.13631)))
("SF_SOLAR" 0 ((5475.11312 7960.03020) (5475.11312 7948.71799)))
("SF_PLANTING" 0 ((5475.11312 267.72342) (5476.16980 282.80543) (5483.70396 297.73416) (5490.19649 301.66007)))
("SF_PLANTING" 0 ((5475.11312 267.72342) (5500.30396 275.41833) (5500.30396 294.11075) (5490.19649 301.66007)))
("SF_SOLAR" 0 ((5478.88428 8122.17195) (5478.88428 8133.48416)))
("SF_SOLAR" 0 ((5478.88428 7978.88394) (5478.88428 7990.19615)))
("SF_SOLAR" 0 ((5478.88428 7914.78133) (5478.88428 7926.09355)))
("SF_PLANTING" 0 ((5482.65419 950.22624) (5516.59084 916.28959)))
("SF_PLANTING" 0 ((5482.65419 950.22624) (5493.96708 965.30826) (5509.04977 976.62048)))
("SF_SOLAR" 0 ((5486.42534 7843.13722) (5520.36199 7843.13722)))
("SF_PLANTING" 0 ((5486.42534 324.28450) (5486.42534 343.13631)))
("SF_PLANTING" 0 ((5486.42534 343.13631) (5497.58948 350.82715) (5527.90305 392.15781)))
("SF_PLANTING" 0 ((5486.42534 324.28450) (5490.19649 301.66007)))
("SF_SOLAR" 0 ((5493.96640 7888.38609) (5493.96640 7880.84468)))
("SF_SOLAR" 0 ((5501.50871 8114.63054) (5501.50871 8125.94276) (5497.73756 8129.71335)))
("SF_SOLAR" 0 ((5501.50871 8069.38167) (5501.50871 8080.69389)))
("SF_SOLAR" 0 ((5501.50871 8020.36199) (5501.50871 8031.67421)))
("SF_SOLAR" 0 ((5501.50871 7978.88394) (5501.50871 7990.19615)))
("SF_SOLAR" 0 ((5501.50871 7963.80090) (5501.50871 7948.71799)))
("SF_SOLAR" 0 ((5501.50871 7926.09355) (5501.50871 7914.78133)))
("SF_SOLAR" 0 ((5965.30894 7850.67873) (5803.16742 7850.68529) (5754.14740 7854.44943) (5746.60633 7854.44943)
(5509.04977 7850.67873)))
("SF_PLANTING" 0 ((5514.70588 3897.05882) (5512.67251 4000.75373) (5509.05600 4015.83710) (5509.04977 5067.87330)))
("SF_ARCHITECTURE" 0 ((5539.21527 5094.26889) (5527.89683 5105.42613) (5501.50826 5100.75328) (5501.50826 5079.18552)
(5509.04977 5067.87330)))
("SF_ARCHITECTURE" 0 ((5539.21527 5094.26889) (5523.98473 5076.46482) (5509.04977 5067.87330)))
("SF_PLANTING" 0 ((5509.04977 3804.67613) (5509.04977 3834.84163)))
("SF_PLANTING" 0 ((5509.04977 3834.84163) (5513.87048 3868.77828) (5520.36199 3880.09050)))
("SF_PLANTING" 0 ((5550.52749 3861.23722) (5542.83835 3843.58744) (5509.04977 3834.84163)))
("SF_PLANTING" 0 ((5509.04977 3804.67613) (5539.21527 3793.51176) (5576.92308 3793.36391)))
("SF_PLANTING" 0 ((5512.82093 1018.09955) (5512.67251 1044.48891) (5509.04977 1052.03620)))
("SF_MASONRY_AND_ARCH" 0 ((5509.04977 1052.03620) (5509.05600 2130.46731) (5512.67251 2145.55079) (5512.82093
2202.11188)))
("SF_PLANTING" 0 ((5509.04977 1006.78733) (5509.04977 976.62048)))
("SF_PLANTING" 0 ((5512.82093 1018.09955) (5509.04977 1006.78733)))
("SF_PLANTING" 0 ((5509.04977 976.62048) (5531.67421 981.44186) (5584.46414 1004.21471) (5606.94072 1022.01776)
(5637.25532 1059.57862)))
("SF_MASONRY_AND_ARCH" 0 ((5520.36199 3009.04977) (5513.87014 3005.12466) (5509.19785 2993.96708) (5512.82093
2956.25939)))
("SF_MASONRY_AND_ARCH" 0 ((5531.67421 2963.80090) (5512.82093 2956.25939)))
("SF_MASONRY_AND_ARCH" 0 ((6089.74333 2115.38462) (6085.81821 2121.73529) (5999.24559 2155.80656) (5882.35294
2189.75011) (5757.91855 2217.04683) (5731.52296 2217.34231) (5682.50419 2228.35905) (5656.10860 2228.65452) (5614.63088
2235.90079) (5512.82093 2239.66437) (5502.71256 2232.27104) (5501.50871 2220.96505) (5502.71256 2209.65973) (5512.82093
2202.11188)))
("SF_MASONRY_AND_ARCH" 0 ((5678.73303 2202.11188) (5625.94310 2202.25962) (5573.15192 2213.42410) (5531.67421
2213.26946) (5512.82093 2202.11188)))
("SF_PLANTING" 0 ((5512.82093 1018.09955) (5542.98643 1021.86934)))
("SF_PLANTING" 0 ((5514.70588 3897.05882) (5520.36199 3880.09050)))
("SF_PLANTING" 0 ((5514.70588 3897.05882) (5542.98643 3898.94378)))
("SF_SOLAR" 0 ((5520.36199 8190.04525) (5516.59084 8197.58665)))
("SF_SOLAR" 0 ((5516.59084 8144.79638) (5516.59084 8156.10860)))
("SF_SOLAR" 0 ((5659.87975 7960.03020) (5634.53394 7986.42534) (5539.06742 8125.94276) (5516.59084 8144.79638)))
("SF_PLANTING" 0 ((5516.59084 916.28959) (5558.06980 916.28959)))
("SF_PLANTING" 0 ((5542.98643 3880.09050) (5520.36199 3880.09050)))
("SF_MASONRY_AND_ARCH" 0 ((5531.67421 2963.80090) (5535.29038 2993.96708) (5531.51957 3001.50181) (5520.36199
3009.04977)))
("SF_MASONRY_AND_ARCH" 0 ((5520.36199 3009.04977) (5520.51007 3058.06912) (5524.12624 3073.15260) (5524.13314
3227.75238)))
("SF_PLANTING" 0 ((5520.36199 263.95079) (5524.13314 237.55656)))
("SF_SOLAR" 0 ((5524.13314 8031.67421) (5524.13314 8020.36199)))
("SF_SOLAR" 0 ((5524.13314 7978.88394) (5524.13314 7990.19615)))
("SF_SOLAR" 0 ((5524.13314 7948.71799) (5524.13314 7960.03020)))
("SF_SOLAR" 0 ((5524.13314 7926.09355) (5524.13314 7911.01052)))
("SF_PLANTING" 0 ((5576.92308 3239.06459) (5565.61086 3242.68122) (5542.98643 3238.90995) (5524.13314 3227.75238)))
("SF_PLANTING" 0 ((5524.13314 294.11765) (5546.75758 301.66007)))
("SF_PLANTING" 0 ((5524.13314 237.55656) (5569.37511 237.70430) (5576.92308 241.32636)))
("SF_SOLAR" 0 ((5535.44536 8073.15226) (5531.67421 8080.69389)))
("SF_MASONRY_AND_ARCH" 0 ((5531.67421 2963.80090) (5546.75758 2956.25939) (5569.37511 2956.25939) (5576.92308
2956.25939)))
("SF_PLANTING" 0 ((5535.44536 444.94627) (5533.92817 437.39910) (5558.06980 395.92760)))
("SF_ARCHITECTURE" 0 ((5539.21527 5094.26889) (5667.42081 5086.72658)))
("SF_PLANTING" 0 ((5542.98643 3880.09050) (5542.98643 3898.94378)))
("SF_PLANTING" 0 ((5558.06980 3917.79830) (5550.37998 3902.86957) (5542.98643 3898.94378)))
("SF_PLANTING" 0 ((5550.52749 3861.23722) (5542.98643 3880.09050)))
("SF_PLANTING" 0 ((5542.98643 1101.05486) (5558.06980 1096.22873) (5579.48948 1074.66063) (5579.49638 1059.58348)
(5573.15192 1052.03620)))
("SF_SOLAR" 0 ((5546.75758 8020.36199) (5546.75758 8031.67421)))
("SF_SOLAR" 0 ((5546.75758 7978.88394) (5546.75758 7990.19615)))
("SF_SOLAR" 0 ((5546.75758 7948.71799) (5546.75758 7960.03020)))
("SF_SOLAR" 0 ((5546.75758 7926.09355) (5546.75758 7914.78133)))
("SF_PLANTING" 0 ((5561.83971 305.42986) (5558.06980 301.66007) (5546.75758 301.66007)))
("SF_PLANTING" 0 ((5546.75758 279.03563) (5546.75758 301.66007)))
("SF_SOLAR" 0 ((5550.52749 8163.65011) (5561.84038 8163.65011) (5765.45962 8163.65011) (5776.77183 8167.42081)))
("SF_SOLAR" 0 ((5550.52749 8163.65011) (5561.83971 8141.02557)))
("SF_SOLAR" 0 ((5561.83971 8141.02557) (5550.52749 8129.71335)))
("SF_PLANTING" 0 ((5550.52749 3978.12930) (5561.84038 3974.20441) (5579.48948 3955.50486) (5581.89152 3925.33937)
(5592.00645 3910.25600)))
("SF_PLANTING" 0 ((5550.52749 3861.23722) (5584.46414 3868.77828)))
("SF_PLANTING" 0 ((5599.54751 912.51980) (5558.06980 916.28959)))
("SF_PLANTING" 0 ((5659.87975 980.39310) (5652.33122 986.73552) (5637.25532 987.78563) (5614.63088 982.96493)
(5577.97975 957.76109) (5559.12590 927.60181) (5558.06980 916.28959)))
("SF_PLANTING" 0 ((5558.06980 395.92760) (5559.26708 377.07296) (5590.80170 339.36652) (5594.57907 312.97229)
(5592.00645 301.66007)))
("SF_PLANTING" 0 ((5654.22364 299.77376) (5636.35984 316.74208) (5624.88643 365.76075) (5609.80995 388.23190)
(5580.69423 403.31471) (5569.38201 402.41290) (5558.06980 395.92760)))
("SF_PLANTING" 0 ((5558.06980 316.74208) (5561.83971 305.42986)))
("SF_SOLAR" 0 ((5561.83971 8141.02557) (5569.38201 8137.25498)))
("SF_PLANTING" 0 ((5569.38201 301.66007) (5561.83971 305.42986)))
("SF_SOLAR" 0 ((5569.38201 8137.25498) (5668.47059 7990.19615) (5726.54830 7922.32274) (5727.59808 7911.01719)
(5723.82726 7904.66686) (5712.66968 7900.89604) (5693.81640 7903.46912)))
("SF_SOLAR" 0 ((5788.08473 8141.02557) (5580.69423 8141.01900) (5569.38201 8137.25498)))
("SF_SOLAR" 0 ((5569.38201 8031.67421) (5569.38201 8020.36199)))
("SF_SOLAR" 0 ((5569.38201 7978.88394) (5569.38201 7990.19615)))
("SF_SOLAR" 0 ((5569.38201 7960.03020) (5569.38201 7952.48869)))
("SF_SOLAR" 0 ((5569.38201 7926.09355) (5569.38201 7914.78133)))
("SF_PLANTING" 0 ((5569.38201 301.66007) (5592.00645 301.66007)))
("SF_PLANTING" 0 ((5569.38201 301.66007) (5569.52986 271.49321) (5576.92308 241.32636)))
("SF_PLANTING" 0 ((5576.92308 3793.36391) (5576.92308 3751.88495)))
("SF_PLANTING" 0 ((5580.69423 3804.67613) (5576.92308 3804.67613) (5576.92308 3793.36391)))
("SF_PLANTING" 0 ((5705.12862 3748.11505) (5663.64966 3751.73100) (5648.56753 3748.26290) (5592.00645 3748.12127)
(5576.92308 3751.88495)))
("SF_PLANTING" 0 ((5603.31867 3239.06459) (5576.92308 3239.06459)))
("SF_MASONRY_AND_ARCH" 0 ((5576.92308 2956.25939) (5573.15192 2986.42534) (5576.62658 3035.44468) (5573.30034
3046.75690) (5576.91686 3084.46482) (5573.15192 3114.63020) (5576.91686 3137.25464) (5576.92308 3239.06459)))
("SF_MASONRY_AND_ARCH" 0 ((5576.92308 2956.25939) (5603.31867 2956.25939)))
("SF_PLANTING" 0 ((5576.92308 241.32636) (5592.00645 241.32636)))
("SF_PLANTING" 0 ((5580.69423 3804.67613) (5599.54751 3793.51176) (5648.56753 3793.51176) (5691.93020 3814.10215)))
("SF_PLANTING" 0 ((5580.69423 3804.67613) (5585.52081 3819.75826) (5606.03314 3842.38269) (5614.63088 3861.23722)))
("SF_PLANTING" 0 ((5580.69423 516.59219) (5574.34977 512.66629) (5570.58586 482.65554) (5581.89152 441.32421)
(5633.48416 409.96086) (5648.56753 395.92760)))
("SF_SOLAR" 0 ((5592.00645 8084.46448) (5584.46414 8076.92308)))
("SF_PLANTING" 0 ((5584.46414 3868.77828) (5599.54751 3867.72851) (5614.63088 3861.23722)))
("SF_PLANTING" 0 ((5584.46414 3868.77828) (5584.61256 3887.63156) (5592.00645 3910.25600)))
("SF_PLANTING" 0 ((5588.23529 279.03563) (5594.57251 290.34785) (5592.00645 301.66007)))
("SF_SOLAR" 0 ((5592.00645 7926.09355) (5592.00645 7914.78133)))
("SF_PLANTING" 0 ((5592.00645 3910.25600) (5614.63088 3910.25600)))
("SF_PLANTING" 0 ((5592.00645 241.32636) (5610.85973 231.06505) (5637.25532 230.16256) (5652.33744 234.98394)
(5663.64966 245.09898)))
("SF_PLANTING" 0 ((5648.56753 279.03563) (5610.85973 259.13156) (5592.00645 241.32636)))
("SF_SOLAR" 0 ((5599.54751 8107.08891) (5629.71301 8099.55407) (5682.50419 8103.31176) (5803.16742 8103.31833)))
("SF_SOLAR" 0 ((5599.54751 7997.73756) (5614.63088 7997.73756)))
("SF_SOLAR" 0 ((5599.54751 7986.42534) (5599.54751 7978.88394)))
("SF_PLANTING" 0 ((5599.54751 912.51980) (5600.75204 905.12511) (5607.09548 901.36086) (5663.64966 901.35464)
(5674.96188 904.97738)))
("SF_PLANTING" 0 ((5599.54751 912.51980) (5648.41912 961.53846) (5659.87975 980.39310)))
("SF_PLANTING" 0 ((5603.31867 3239.06459) (5644.79638 3239.06459)))
("SF_MASONRY_AND_ARCH" 0 ((5603.31867 3239.06459) (5603.31867 2956.25939)))
("SF_MASONRY_AND_ARCH" 0 ((5641.02523 2956.25939) (5603.31867 2956.25939)))
("SF_SOLAR" 0 ((5610.85973 8058.06946) (5607.08857 8046.75724)))
("SF_SOLAR" 0 ((5610.85973 8129.71335) (5614.63088 8118.40113)))
("SF_SOLAR" 0 ((5614.63088 7948.71799) (5614.63088 7960.03020)))
("SF_SOLAR" 0 ((5614.63088 7918.55204) (5614.63088 7926.09355)))
("SF_PLANTING" 0 ((5625.94310 3898.94378) (5622.17195 3898.94378) (5614.63088 3910.25600)))
("SF_PLANTING" 0 ((5693.81640 4000.75373) (5686.26787 3990.49785) (5652.33744 3974.20441) (5626.09095 3947.96380)
(5615.82817 3932.88043) (5614.63088 3910.25600)))
("SF_PLANTING" 0 ((5625.94310 3868.77828) (5614.63088 3861.23722)))
("SF_ARCHITECTURE" 0 ((5618.40079 5260.18100) (5618.40079 5248.86878)))
("SF_ARCHITECTURE" 0 ((6236.80215 5098.03880) (6195.32455 5106.63032) (6108.59729 5142.23846) (5950.22624 5195.02839)
(5848.41629 5219.75283) (5769.23077 5244.04808) (5727.75305 5249.01686) (5682.50419 5260.03292) (5637.25532 5263.93903)
(5618.40079 5260.18100)))
("SF_ARCHITECTURE" 0 ((5791.85520 5211.16097) (5776.77183 5211.30939) (5746.60633 5222.31923) (5708.89853 5226.39242)
(5686.27410 5233.63756) (5633.49038 5237.71120) (5618.40079 5248.86878)))
("SF_PLANTING" 0 ((5629.71301 3996.98382) (5622.17195 3996.98382)))
("SF_PLANTING" 0 ((5625.94310 3868.77828) (5625.94310 3898.94378)))
("SF_PLANTING" 0 ((5625.94310 3898.94378) (5648.56753 3912.82952) (5659.87975 3913.87907) (5674.59378 3909.89446)
(5678.73303 3887.63156)))
("SF_PLANTING" 0 ((5625.94310 3868.77828) (5644.79638 3868.77828)))
("SF_PLANTING" 0 ((5625.94310 516.59219) (5652.33744 512.81957) (5769.23077 516.59219)))
("SF_SOLAR" 0 ((5837.10407 8054.29864) (5825.79186 8058.06290) (5633.48416 8058.06946)))
("SF_ARCHITECTURE" 0 ((5633.48416 5603.31867) (5637.40928 5596.97421) (6662.89593 5592.00645)))
("SF_ARCHITECTURE" 0 ((5633.48416 5603.31867) (5648.56753 5618.40124) (5776.77183 5618.40124) (5799.39695 5618.40124)
(6251.88563 5618.40124)))
("SF_SOLAR" 0 ((5637.25532 8133.48416) (5637.25532 8118.40113)))
("SF_SOLAR" 0 ((5637.25532 8084.46448) (5641.02523 8073.15226)))
("SF_SOLAR" 0 ((5637.25532 7914.78133) (5644.79638 7926.09355)))
("SF_MASONRY_AND_ARCH" 0 ((5641.02523 2956.25939) (5674.96188 2956.25939)))
("SF_MASONRY_AND_ARCH" 0 ((5641.02523 2956.25939) (5644.79638 3239.06459)))
("SF_PLANTING" 0 ((5644.79638 3868.77828) (5691.93020 3814.10215)))
("SF_PLANTING" 0 ((5644.79638 3868.77828) (5678.73303 3887.63156)))
("SF_PLANTING" 0 ((5674.96188 3239.06459) (5644.79638 3239.06459)))
("SF_PLANTING" 0 ((5648.56753 1021.86934) (5644.79638 1033.18156)))
("SF_SOLAR" 0 ((5656.10860 7993.96674) (5648.56753 7982.65452)))
("SF_PLANTING" 0 ((5671.19197 395.92760) (5648.56753 395.92760)))
("SF_PLANTING" 0 ((5648.56753 388.38518) (5648.56753 395.92760)))
("SF_PLANTING" 0 ((5648.56753 279.03563) (5654.91097 275.10973) (5657.30622 256.41120) (5663.64966 245.09898)))
("SF_PLANTING" 0 ((5654.22364 299.77376) (5648.56753 279.03563)))
("SF_PLANTING" 0 ((5652.33744 4049.77376) (5652.33744 4057.31482)))
("SF_PLANTING" 0 ((5652.33744 1082.20305) (5652.33744 1089.74265) (5659.87975 1097.28507)))
("SF_PLANTING" 0 ((5654.22364 299.77376) (5697.58631 275.26301)))
("SF_PLANTING" 0 ((5654.22364 299.77376) (5667.26301 312.96810) (5674.96188 328.05430)))
("SF_SOLAR" 0 ((5656.10860 8069.38167) (5659.87975 8073.15226) (5659.87975 8084.46448)))
("SF_SOLAR" 0 ((5848.41629 8050.52783) (5829.56233 8043.13450) (5656.10860 8042.98643)))
("SF_PLANTING" 0 ((5656.10860 365.76075) (5674.96188 343.13631)))
("SF_SOLAR" 0 ((5667.42081 7941.17647) (5659.87975 7960.03020)))
("SF_SOLAR" 0 ((5659.87975 7960.03020) (5667.42081 7975.11312)))
("SF_PLANTING" 0 ((5659.87975 980.39310) (5705.12794 988.98982) (5716.44084 995.47511)))
("SF_PLANTING" 0 ((5697.58631 245.09898) (5663.64966 245.09898)))
("SF_SOLAR" 0 ((5855.95803 8009.04977) (5844.64581 8012.81403) (5705.12862 8012.81403) (5686.27410 8009.06290)
(5667.42081 8012.82059)))
("SF_SOLAR" 0 ((5667.42081 7941.17647) (5688.98857 7918.55204) (5693.81640 7903.46912)))
("SF_ARCHITECTURE" 0 ((5739.06527 5064.10215) (5705.12862 5064.25057) (5678.73303 5069.07783) (5668.62534 5079.17930)
(5667.42081 5086.72658)))
("SF_ARCHITECTURE" 0 ((5739.06527 5079.18552) (5731.51674 5086.57262) (5686.27410 5090.49152) (5667.42081 5086.72658)))
("SF_PLANTING" 0 ((5674.96188 904.97738) (5671.19197 923.83201)))
("SF_PLANTING" 0 ((5701.35747 392.15781) (5678.73925 392.30486) (5671.19197 395.92760)))
("SF_PLANTING" 0 ((5671.19197 395.92760) (5679.78247 410.85633) (5686.27410 414.78224)))
("SF_MASONRY_AND_ARCH" 0 ((5674.96188 2956.25939) (5678.73303 2982.65486) (5674.96878 3012.82025) (5674.96188
3239.06459)))
("SF_PLANTING" 0 ((5716.44084 3239.06459) (5701.35747 3242.83586) (5674.96188 3239.06459)))
("SF_MASONRY_AND_ARCH" 0 ((5720.21075 2956.25939) (5701.35747 2956.25939) (5674.96188 2956.25939)))
("SF_PLANTING" 0 ((5674.96188 904.97738) (5716.43394 905.12511) (5723.98190 908.74717)))
("SF_PLANTING" 0 ((5674.96188 328.05430) (5674.96188 343.13631)))
("SF_PLANTING" 0 ((5674.96188 343.13631) (5708.89853 350.67873)))
("SF_PLANTING" 0 ((5674.96188 328.05430) (5697.58631 320.66719) (5712.66968 328.05430)))
("SF_SOLAR" 0 ((5678.73303 8031.67421) (5682.50419 8020.36199)))
("SF_PLANTING" 0 ((5718.32579 3874.43439) (5697.58631 3886.58201) (5678.73303 3887.63156)))
("SF_MASONRY_AND_ARCH" 0 ((5678.73303 2526.39491) (5678.73303 2560.33156)))
("SF_MASONRY_AND_ARCH" 0 ((5678.73303 2526.39491) (5693.81640 2522.63066) (5893.66516 2522.61821) (5912.51912
2518.86018) (5938.91403 2522.62443)))
("SF_SOLAR" 0 ((5682.50419 8084.46448) (5682.50419 8069.38167)))
("SF_MASONRY_AND_ARCH" 0 ((5690.04525 2635.74661) (5682.50419 2635.74661)))
("SF_MASONRY_AND_ARCH" 0 ((5690.04525 2605.58043) (5682.50419 2601.80995)))
("SF_SOLAR" 0 ((5690.04525 7948.71799) (5686.27410 7941.17647)))
("SF_PLANTING" 0 ((5693.81640 1127.45192) (5683.84989 1142.53394) (5686.27410 1153.84615)))
("SF_PLANTING" 0 ((5701.35747 392.15781) (5696.38903 407.23292) (5686.27410 414.78224)))
("SF_PLANTING" 0 ((5690.04525 429.86425) (5686.27410 414.78224)))
("SF_MASONRY_AND_ARCH" 0 ((6078.43111 2100.30192) (6063.34842 2101.35826) (6014.32907 2121.72839) (5938.91403
2144.49434) (5806.93790 2178.43100) (5757.91855 2183.40633) (5716.44084 2194.28088) (5690.04525 2194.57014)))
("SF_PLANTING" 0 ((5705.12862 3804.67613) (5691.93020 3814.10215)))
("SF_PLANTING" 0 ((5718.32579 3874.43439) (5707.70124 3834.84163) (5691.93020 3814.10215)))
("SF_SOLAR" 0 ((5693.81640 8001.50837) (5712.66968 7997.73756) (5848.41629 7997.88563) (5878.58247 8005.13100)
(5889.89468 8001.50837)))
("SF_ARCHITECTURE" 0 ((5886.12342 4498.49129) (5766.51007 4332.57919) (5693.81640 4219.45701)))
("SF_SOLAR" 0 ((5705.12862 7933.63495) (5697.58631 7929.86425)))
("SF_MASONRY_AND_ARCH" 0 ((5712.66968 2665.91278) (5697.58631 2665.91278)))
("SF_PLANTING" 0 ((5697.58631 245.09898) (5697.58631 275.26301)))
("SF_PLANTING" 0 ((5723.98190 305.42986) (5697.58631 275.26301)))
("SF_PLANTING" 0 ((5697.58631 245.09898) (5723.98190 245.09898)))
("SF_PLANTING" 0 ((5701.35747 3963.04717) (5731.52296 3914.02715)))
("SF_PLANTING" 0 ((5705.12862 3616.13903) (5697.58631 3608.59729) (5701.35747 3601.05554)))
("SF_PLANTING" 0 ((5701.35747 392.15781) (5720.21075 373.30317)))
("SF_SOLAR" 0 ((5705.12862 8125.94276) (5705.12862 8114.63054)))
("SF_SOLAR" 0 ((5705.12862 8069.38167) (5705.12862 8080.69389)))
("SF_SOLAR" 0 ((5705.12862 8035.44502) (5705.12862 8020.36199)))
("SF_SOLAR" 0 ((5908.74785 7975.11312) (5897.43563 7971.34887) (5705.12862 7971.34231)))
("SF_PLANTING" 0 ((5705.12862 3804.67613) (5705.12862 3748.11505)))
("SF_PLANTING" 0 ((5705.12862 3804.67613) (5757.91855 3808.44604)))
("SF_PLANTING" 0 ((5723.98190 3740.57274) (5705.12862 3748.11505)))
("SF_MASONRY_AND_ARCH" 0 ((5705.12862 1289.59276) (5749.17964 1353.69627) (5774.05735 1398.94514) (5794.57624
1421.56957) (5920.06007 1606.33484)))
("SF_SOLAR" 0 ((5708.89853 7986.42534) (5708.89853 7978.88394)))
("SF_PLANTING" 0 ((5712.66968 328.05430) (5708.89853 350.67873)))
("SF_PLANTING" 0 ((5720.21075 373.30317) (5708.89853 350.67873)))
("SF_PLANTING" 0 ((5723.98190 328.05430) (5712.66968 328.05430)))
("SF_PLANTING" 0 ((5716.44084 3239.06459) (5750.37749 3239.06459)))
("SF_MASONRY_AND_ARCH" 0 ((5720.21075 2956.25939) (5716.44706 2982.65486) (5716.44084 3239.06459)))
("SF_PLANTING" 0 ((5716.44084 1018.09955) (5716.44084 995.47511)))
("SF_PLANTING" 0 ((5750.37749 1176.47059) (5749.17274 1138.76414) (5720.36572 1112.36708) (5693.97738 1074.66063)
(5706.33247 1025.64683) (5716.44084 1018.09955)))
("SF_PLANTING" 0 ((5716.44084 1018.09955) (5726.54830 1029.41176) (5735.29412 1055.80600)))
("SF_PLANTING" 0 ((5723.98190 995.47511) (5716.44084 995.47511)))
("SF_PLANTING" 0 ((5718.32579 3874.43439) (5727.68541 3866.27296) (5754.14740 3861.23722)))
("SF_PLANTING" 0 ((5718.32579 3874.43439) (5726.48100 3883.79400) (5731.52296 3914.02715)))
("SF_MASONRY_AND_ARCH" 0 ((5750.37749 2956.25939) (5720.21075 2956.25939)))
("SF_PLANTING" 0 ((5720.21075 373.30317) (5739.06527 373.30317)))
("SF_PLANTING" 0 ((5723.98190 995.47511) (5735.29412 957.76867)))
("SF_PLANTING" 0 ((5761.68971 1010.55713) (5735.29412 1005.58247) (5723.98190 995.47511)))
("SF_PLANTING" 0 ((5735.29412 908.74717) (5723.98190 908.74717)))
("SF_PLANTING" 0 ((5723.98190 908.74717) (5735.29412 957.76867)))
("SF_PLANTING" 0 ((5723.98190 328.05430) (5723.98190 305.42986)))
("SF_PLANTING" 0 ((5723.98190 328.05430) (5737.86708 343.13631) (5741.78563 354.44853) (5739.06527 373.30317)))
("SF_PLANTING" 0 ((5723.98190 305.42986) (5742.68733 297.73416) (5753.63122 268.77907) (5723.98190 245.09898)))
("SF_PLANTING" 0 ((5822.02138 241.32636) (5799.39695 230.16256) (5750.37749 230.16256) (5735.29412 234.98394)
(5723.98190 245.09898)))
("SF_SOLAR" 0 ((5727.75305 8114.63054) (5727.75305 8129.71335)))
("SF_SOLAR" 0 ((5727.75305 8080.69389) (5727.75305 8069.38167)))
("SF_SOLAR" 0 ((5727.75305 8035.44502) (5727.75305 8020.36199)))
("SF_SOLAR" 0 ((5803.16742 8088.23529) (5731.52296 8088.23529)))
("SF_SOLAR" 0 ((5731.52296 7937.40577) (5901.20690 7937.39921) (5916.28959 7933.93111) (5931.37229 7941.17647)))
("SF_SOLAR" 0 ((5961.53846 7903.46912) (5769.23077 7903.46256) (5731.52296 7899.69830)))
("SF_PLANTING" 0 ((5761.68971 3914.02715) (5731.52296 3914.02715)))
("SF_PLANTING" 0 ((5756.03360 948.33993) (5735.29412 957.76867)))
("SF_PLANTING" 0 ((5735.29412 908.74717) (5750.37749 901.35532) (5788.08473 897.58337) (5821.87285 909.95204)
(5833.33360 923.83201)))
("SF_PLANTING" 0 ((5735.29412 908.74717) (5756.03360 948.33993)))
("SF_ARCHITECTURE" 0 ((5739.06527 5079.18552) (5791.85520 5075.26652) (5810.70916 5068.02138) (5844.63891 5062.90486)
(5852.18676 5056.56109)))
("SF_ARCHITECTURE" 0 ((5739.06527 5079.18552) (5739.06527 5064.10215)))
("SF_ARCHITECTURE" 0 ((5739.06527 5064.10215) (5750.37749 5053.84661) (5780.54299 5052.64208) (5806.93790 5041.62613)
(5844.64581 5041.47771)))
("SF_MASONRY_AND_ARCH" 0 ((5908.74785 2631.97590) (5893.66516 2631.97590) (5814.47964 2631.97590) (5773.00192
2620.50928) (5757.91855 2613.27681) (5739.06527 2613.12217)))
("SF_PLANTING" 0 ((5765.45962 403.47002) (5746.76097 392.15023) (5739.06527 373.30317)))
("SF_SOLAR" 0 ((5750.37749 7865.76165) (5746.60633 7888.38609)))
("SF_SOLAR" 0 ((5750.37749 8220.21109) (5754.14740 8227.75271)))
("SF_SOLAR" 0 ((5750.37749 8133.48416) (5750.37749 8114.63054)))
("SF_SOLAR" 0 ((5750.37749 8069.38167) (5750.37749 8080.69389)))
("SF_SOLAR" 0 ((5750.37749 8031.67421) (5750.37749 8024.13281)))
("SF_SOLAR" 0 ((5750.37749 7986.42534) (5750.37749 7978.88394)))
("SF_SOLAR" 0 ((5750.37749 7960.03020) (5750.37749 7948.71799)))
("SF_PLANTING" 0 ((5750.37749 3729.26052) (5757.91855 3725.49061)))
("SF_MASONRY_AND_ARCH" 0 ((5750.37749 2956.25939) (5750.37749 3239.06459)))
("SF_PLANTING" 0 ((5750.37749 3239.06459) (5757.92477 3242.68812) (5784.31346 3242.83586)))
("SF_MASONRY_AND_ARCH" 0 ((5750.37749 2956.25939) (5784.31346 2956.25939)))
("SF_PLANTING" 0 ((5750.37749 1070.89084) (5765.45962 1082.20305)))
("SF_PLANTING" 0 ((5754.14740 3861.23722) (5757.91855 3808.44604)))
("SF_PLANTING" 0 ((5780.54299 3865.00713) (5754.14740 3861.23722)))
("SF_PLANTING" 0 ((5803.16742 3653.84615) (5776.77183 3639.81946) (5754.14740 3638.76278)))
("SF_PLANTING" 0 ((5756.03360 948.33993) (5776.77183 935.14423)))
("SF_PLANTING" 0 ((5756.03360 948.33993) (5780.54299 969.08088)))
("SF_ARCHITECTURE" 0 ((5757.91855 4411.76471) (5808.13586 4490.94400) (5818.25011 4498.49129)))
("SF_PLANTING" 0 ((5806.93790 3804.67613) (5757.91855 3808.44604)))
("SF_PLANTING" 0 ((5780.54299 3710.40724) (5772.99502 3699.09502) (5757.91855 3687.78281)))
("SF_PLANTING" 0 ((5761.68971 3914.02715) (5761.68971 3929.11052)))
("SF_PLANTING" 0 ((5780.54299 3895.17387) (5803.16742 3909.19989) (5825.79186 3911.46075) (5836.04774 3921.56889)
(5839.52206 3932.88043) (5829.56233 3942.98880) (5810.71538 3949.02048) (5788.08473 3973.15464) (5780.54299 3974.19785)
(5765.60803 3963.04649) (5758.97523 3951.73495) (5758.06663 3936.65781) (5761.68971 3929.11052)))
("SF_PLANTING" 0 ((5788.08473 3932.88043) (5761.68971 3929.11052)))
("SF_PLANTING" 0 ((5780.54299 3895.17387) (5761.68971 3914.02715)))
("SF_MASONRY_AND_ARCH" 0 ((5761.68971 2665.91278) (5773.00192 2662.14774) (5814.47964 2662.28925) (5829.56233
2665.90656) (6078.43111 2665.91278) (6119.90950 2662.14152)))
("SF_PLANTING" 0 ((5761.68971 1010.55713) (5765.45962 1003.01753) (5773.00192 1003.01753)))
("SF_PLANTING" 0 ((5761.68971 1010.55713) (5769.37885 1029.41176) (5780.54299 1039.52602) (5791.84830 1042.24084)
(5799.24231 1033.18156) (5799.39695 1010.55713)))
("SF_SOLAR" 0 ((5769.23077 7926.09355) (5765.45962 7914.78133)))
("SF_PLANTING" 0 ((5765.45962 403.47002) (5773.00192 388.38518)))
("SF_PLANTING" 0 ((5765.45962 403.47002) (5773.14977 414.63382) (5788.08473 422.02636) (5806.93790 411.00962)))
("SF_PLANTING" 0 ((5776.77183 3725.49061) (5769.23077 3725.49061)))
("SF_SOLAR" 0 ((5776.77183 8118.40113) (5773.00192 8133.48416)))
("SF_SOLAR" 0 ((5773.00192 8080.69389) (5773.00192 8069.38167)))
("SF_SOLAR" 0 ((5773.00192 8035.44502) (5773.00192 8020.36199)))
("SF_MASONRY_AND_ARCH" 0 ((5773.00192 1496.98247) (5804.21686 1546.00396) (5818.25011 1561.08597)))
("SF_PLANTING" 0 ((5780.54299 969.08088) (5773.14977 984.16290) (5773.00192 1003.01753)))
("SF_PLANTING" 0 ((5799.39695 1010.55713) (5773.00192 1003.01753)))
("SF_PLANTING" 0 ((5776.77183 3725.49061) (5780.54299 3710.40724)))
("SF_PLANTING" 0 ((5776.77183 3725.49061) (5803.16742 3743.28722) (5840.87455 3751.88495)))
("SF_PLANTING" 0 ((5788.08473 328.05430) (5776.77183 324.28450)))
("SF_PLANTING" 0 ((5780.54299 3895.17387) (5780.54299 3865.00713)))
("SF_PLANTING" 0 ((5816.36527 3846.15385) (5791.85520 3863.80984) (5780.54299 3865.00713)))
("SF_PLANTING" 0 ((5840.87455 3751.88495) (5835.90611 3733.03167) (5822.02138 3719.14649) (5780.54299 3710.40724)))
("SF_PLANTING" 0 ((5780.54299 969.08088) (5810.70916 969.08088)))
("SF_PLANTING" 0 ((5822.02138 3239.06459) (5784.31346 3242.83586)))
("SF_MASONRY_AND_ARCH" 0 ((5784.31346 2956.25939) (5784.31346 3242.83586)))
("SF_MASONRY_AND_ARCH" 0 ((5784.31346 2956.25939) (5818.25011 2956.25939)))
("SF_PLANTING" 0 ((5803.16742 320.51188) (5788.08473 328.05430)))
("SF_PLANTING" 0 ((5803.16742 358.22115) (5793.05939 346.90894) (5788.08473 328.05430)))
("SF_SOLAR" 0 ((5795.62568 7990.19615) (5791.85520 7982.65452)))
("SF_PLANTING" 0 ((5791.85520 271.49321) (5822.02138 241.32636)))
("SF_SOLAR" 0 ((5795.62568 8069.38167) (5795.62568 8080.69389)))
("SF_SOLAR" 0 ((5795.62568 8020.36199) (5795.62568 8035.44502)))
("SF_SOLAR" 0 ((5795.62568 7960.03020) (5795.62568 7948.71799)))
("SF_SOLAR" 0 ((5795.62568 7926.09355) (5795.62568 7914.78133)))
("SF_PLANTING" 0 ((5810.70916 969.08088) (5806.78326 1003.00995) (5799.39695 1010.55713)))
("SF_SOLAR" 0 ((5803.16742 8171.19163) (5810.70916 8174.96222)))
("SF_SOLAR" 0 ((5822.02138 8095.77670) (5810.71538 8096.97443) (5803.16742 8103.31833)))
("SF_SOLAR" 0 ((5810.70916 8110.85973) (5803.16742 8103.31833)))
("SF_PLANTING" 0 ((5803.16742 358.22115) (5818.25011 358.22115)))
("SF_PLANTING" 0 ((5806.93790 399.69740) (5795.78032 388.38518) (5795.78032 373.30317) (5803.16742 358.22115)))
("SF_PLANTING" 0 ((5803.16742 320.51188) (5804.37161 305.42986) (5818.25011 294.11765)))
("SF_PLANTING" 0 ((5803.16742 320.51188) (5822.02138 328.05430)))
("SF_PLANTING" 0 ((5806.93790 3804.67613) (5822.02138 3790.64943) (5859.72851 3770.73948)))
("SF_PLANTING" 0 ((5816.36527 3846.15385) (5807.08563 3827.30057) (5806.93790 3804.67613)))
("SF_PLANTING" 0 ((5806.93790 399.69740) (5806.93790 411.00962)))
("SF_PLANTING" 0 ((5806.93790 411.00962) (5829.56233 426.09446)))
("SF_PLANTING" 0 ((5806.93790 399.69740) (5817.19378 388.38518) (5820.82342 369.53337) (5818.25011 358.22115)))
("SF_ARCHITECTURE" 0 ((5822.02138 5199.84876) (5810.70916 5199.84876)))
("SF_PLANTING" 0 ((5833.33360 923.83201) (5821.12658 938.91403) (5810.70916 969.08088)))
("SF_SOLAR" 0 ((5818.25011 8069.38167) (5814.47964 8080.69389)))
("SF_PLANTING" 0 ((5816.36527 3846.15385) (5825.72421 3839.81007) (5837.10407 3838.76063) (5871.03382 3847.35147)
(5878.58247 3853.69491)))
("SF_PLANTING" 0 ((5816.36527 3846.15385) (5841.02308 3876.17149) (5867.27025 3887.63156)))
("SF_SOLAR" 0 ((5818.25011 8024.13281) (5818.25011 8031.67421)))
("SF_SOLAR" 0 ((5818.25011 7978.88394) (5818.25011 7990.19615)))
("SF_SOLAR" 0 ((5818.25011 7914.78133) (5818.25011 7926.09355)))
("SF_ARCHITECTURE" 0 ((5829.56233 4498.49129) (5818.25011 4498.49129)))
("SF_ARCHITECTURE" 0 ((5837.10407 4517.34581) (5825.79808 4513.42002) (5818.25011 4498.49129)))
("SF_MASONRY_AND_ARCH" 0 ((5837.10407 2956.25939) (5818.25011 2956.25939)))
("SF_MASONRY_AND_ARCH" 0 ((5825.79186 3005.27930) (5818.39864 2993.96708) (5818.25011 2956.25939)))
("SF_MASONRY_AND_ARCH" 0 ((6150.07568 2292.60962) (5920.06007 2360.33439) (5867.27025 2371.64740) (5818.25011
2371.79514)))
("SF_MASONRY_AND_ARCH" 0 ((5855.95803 2345.39943) (5829.71086 2353.99751) (5818.25011 2371.79514)))
("SF_MASONRY_AND_ARCH" 0 ((5829.56233 1553.54355) (5818.25011 1561.08597)))
("SF_MASONRY_AND_ARCH" 0 ((5829.56233 1579.94061) (5818.25011 1561.08597)))
("SF_PLANTING" 0 ((5818.25011 358.22115) (5821.87364 350.67183) (5822.02138 328.05430)))
("SF_PLANTING" 0 ((5818.25011 294.11765) (5840.87455 294.11765)))
("SF_PLANTING" 0 ((5818.25011 294.11765) (5818.25011 286.57523)))
("SF_MASONRY_AND_ARCH" 0 ((5822.02138 3239.06459) (5822.16912 3186.27477) (5829.54921 3103.31799) (5825.93959
3088.23529) (5825.79186 3005.27930)))
("SF_PLANTING" 0 ((5882.35294 3235.29412) (5871.04072 3242.68122) (5822.02138 3239.06459)))
("SF_PLANTING" 0 ((5840.87455 305.42986) (5829.42081 324.12919) (5822.02138 328.05430)))
("SF_PLANTING" 0 ((5848.41629 241.32636) (5822.02138 241.32636)))
("SF_PLANTING" 0 ((5825.79186 3525.64129) (5837.10407 3536.95351)))
("SF_MASONRY_AND_ARCH" 0 ((5837.10407 2956.25939) (5836.94943 2997.73066) (5833.18507 3004.07511) (5825.79186
3005.27930)))
("SF_ARCHITECTURE" 0 ((5829.56233 4498.49129) (5829.56233 4487.17907)))
("SF_ARCHITECTURE" 0 ((5829.56233 4498.49129) (5835.90611 4506.03982) (5837.10407 4517.34581)))
("SF_MASONRY_AND_ARCH" 0 ((5829.56233 1579.94061) (5837.10407 1579.94061)))
("SF_MASONRY_AND_ARCH" 0 ((5829.56233 1579.94061) (5837.25181 1594.86799) (5848.41629 1598.79242)))
("SF_PLANTING" 0 ((5852.18676 426.09446) (5829.56233 426.09446)))
("SF_PLANTING" 0 ((5855.95803 512.81957) (5829.71086 505.12466) (5815.52907 475.11312) (5815.53597 463.80090)
(5828.35826 444.94627) (5829.56233 426.09446)))
("SF_PLANTING" 0 ((5833.33360 3567.11889) (5838.16041 3578.43111) (5852.18676 3593.51459)))
("SF_PLANTING" 0 ((5833.33360 923.83201) (5840.87455 923.83201)))
("SF_ARCHITECTURE" 0 ((5837.10407 4517.34581) (5857.15520 4555.05238) (5896.23846 4600.30124) (5953.99672 4694.57014)))
("SF_PLANTING" 0 ((5837.10407 3416.28959) (5852.18676 3427.60181)))
("SF_MASONRY_AND_ARCH" 0 ((5837.10407 2956.25939) (5871.04072 2956.25939)))
("SF_MASONRY_AND_ARCH" 0 ((5837.10407 1568.62839) (5837.10407 1579.94061)))
("SF_MASONRY_AND_ARCH" 0 ((5837.10407 1579.94061) (5847.21210 1591.24525) (5848.41629 1598.79242)))
("SF_SOLAR" 0 ((5844.64581 8020.36199) (5840.87455 8035.44502)))
("SF_SOLAR" 0 ((5840.87455 7978.88394) (5840.87455 7990.19615)))
("SF_SOLAR" 0 ((5840.87455 7960.03020) (5840.87455 7952.48869)))
("SF_PLANTING" 0 ((5840.87455 3751.88495) (5859.72851 3763.19717)))
("SF_PLANTING" 0 ((5840.87455 923.83201) (5852.18676 908.89559) (5867.27025 901.35532) (5897.42941 902.41097)
(5908.74785 916.28959)))
("SF_PLANTING" 0 ((5886.12342 950.22624) (5859.72851 941.48665) (5840.87455 923.83201)))
("SF_PLANTING" 0 ((5840.87455 305.42986) (5855.95803 305.42986)))
("SF_PLANTING" 0 ((5840.87455 305.42986) (5840.87455 294.11765)))
("SF_PLANTING" 0 ((5852.18676 260.18100) (5842.07873 271.49321) (5840.87455 294.11765)))
("SF_ARCHITECTURE" 0 ((5882.35294 5030.16550) (5855.95803 5031.22217) (5844.64581 5041.47771)))
("SF_ARCHITECTURE" 0 ((5852.18676 5056.56109) (5844.64581 5041.47771)))
("SF_SOLAR" 0 ((5848.41629 8163.65000) (6067.11889 8163.65000)))
("SF_MASONRY_AND_ARCH" 0 ((5852.18676 3201.35747) (5848.41629 3193.81572)))
("SF_MASONRY_AND_ARCH" 0 ((5987.93337 1813.72455) (5892.46799 1666.81414) (5857.15520 1621.41686) (5848.41629
1598.79242)))
("SF_PLANTING" 0 ((5908.74785 233.78676) (5897.43563 230.16256) (5867.27025 230.16256) (5848.41629 241.32636)))
("SF_PLANTING" 0 ((5852.18676 260.18100) (5848.41629 241.32636)))
("SF_ARCHITECTURE" 0 ((5852.18676 5056.56109) (5885.96878 5051.59265) (5889.89468 5045.24887)))
("SF_PLANTING" 0 ((5852.18676 3623.68066) (5852.18676 3593.51459)))
("SF_PLANTING" 0 ((5884.23857 3589.74333) (5852.18676 3593.51459)))
("SF_PLANTING" 0 ((5852.18676 426.09446) (5852.18676 414.78224)))
("SF_PLANTING" 0 ((5852.18676 426.09446) (5848.56471 475.11312) (5855.95803 512.81957)))
("SF_PLANTING" 0 ((5897.43563 369.53337) (5878.43394 403.46244) (5863.49898 413.72511) (5852.18676 414.78224)))
("SF_PLANTING" 0 ((5871.04072 346.90894) (5853.24321 377.07296) (5852.18676 414.78224)))
("SF_PLANTING" 0 ((5852.18676 260.18100) (5867.27025 282.80543)))
("SF_PLANTING" 0 ((5855.95803 520.36199) (5855.95803 512.81957)))
("SF_PLANTING" 0 ((5867.27025 282.80543) (5855.95803 305.42986)))
("SF_PLANTING" 0 ((5871.04072 346.90894) (5866.06606 320.51188) (5855.95803 305.42986)))
("SF_PLANTING" 0 ((5859.72851 3763.19717) (5859.72851 3770.73948)))
("SF_PLANTING" 0 ((5874.81120 3778.28054) (5859.72851 3770.73948)))
("SF_PLANTING" 0 ((5859.72851 3763.19717) (5867.12862 3759.27229) (5873.75486 3748.11505) (5878.58247 3702.86618)))
("SF_PLANTING" 0 ((5859.72851 3657.61731) (5878.58247 3661.38722)))
("SF_PLANTING" 0 ((5904.97738 984.16290) (5896.23156 1006.78733) (5882.35294 1017.93733) (5874.81120 1016.89468)
(5864.55543 1006.78733) (5857.16210 991.71018) (5859.72851 984.16290)))
("SF_SOLAR" 0 ((5863.49898 7948.71799) (5863.49898 7960.03020)))
("SF_SOLAR" 0 ((5863.49898 7914.78133) (5863.49898 7929.86425)))
("SF_SOLAR" 0 ((5867.27025 8182.50385) (5867.27025 8174.96222)))
("SF_PLANTING" 0 ((5878.58247 3853.69491) (5873.61335 3880.08428) (5867.27025 3887.63156)))
("SF_PLANTING" 0 ((5889.89468 3902.71493) (5882.34604 3901.51041) (5867.27025 3887.63156)))
("SF_PLANTING" 0 ((5878.58247 3702.86618) (5867.27025 3702.86618)))
("SF_MASONRY_AND_ARCH" 0 ((6251.88563 2205.88235) (6172.70011 2246.31120) (6052.03620 2291.55317) (5953.99672
2316.43190) (5935.14355 2325.49604) (5916.28959 2327.74412) (5901.20690 2336.80204) (5867.27025 2337.85848)))
("SF_PLANTING" 0 ((5867.27025 282.80543) (5882.35294 283.86176) (5893.51742 290.49491) (5913.57477 320.36482)
(5923.83133 328.05430)))
("SF_SOLAR" 0 ((5871.04072 8141.02557) (5886.12342 8144.78982) (5995.47511 8144.78982) (6040.72398 8141.02568)
(6059.57794 8144.79638)))
("SF_SOLAR" 0 ((5871.04072 7990.19615) (5878.58247 7982.65452)))
("SF_MASONRY_AND_ARCH" 0 ((5901.20690 2956.25939) (5871.04072 2956.25939)))
("SF_MASONRY_AND_ARCH" 0 ((5882.35294 3235.29412) (5874.95973 3220.21143) (5871.04072 2956.25939)))
("SF_PLANTING" 0 ((5897.43563 369.53337) (5893.51052 354.59695) (5882.35294 347.96459) (5871.04072 346.90894)))
("SF_PLANTING" 0 ((5874.81120 3778.28054) (5912.51912 3778.13247) (5927.60181 3770.73948)))
("SF_PLANTING" 0 ((5920.06007 3853.69491) (5919.69140 3835.89140) (5886.27805 3808.44604) (5874.81120 3778.28054)))
("SF_PLANTING" 0 ((5884.23857 3589.74333) (5882.64910 3555.95520) (5874.81120 3548.26572)))
("SF_PLANTING" 0 ((5920.06007 3853.69491) (5878.58247 3853.69491)))
("SF_PLANTING" 0 ((5878.58247 3702.86618) (5878.58247 3661.38722)))
("SF_PLANTING" 0 ((5884.23857 3589.74333) (5885.97568 3627.45057) (5878.58247 3661.38722)))
("SF_PLANTING" 0 ((5878.58247 3408.74785) (5884.92557 3412.67376) (5891.09876 3450.07851) (5907.54378 3465.30894)
(5908.74785 3499.24559)))
("SF_ARCHITECTURE" 0 ((5927.60181 5018.85328) (5897.43563 5019.90373) (5886.27805 5023.81550) (5882.35294 5030.16550)))
("SF_ARCHITECTURE" 0 ((5882.35294 5030.16550) (5889.89468 5045.24887)))
("SF_PLANTING" 0 ((5882.35294 3936.65158) (5889.89468 3902.71493)))
("SF_PLANTING" 0 ((5882.35294 3344.64581) (5908.60011 3345.84989) (5914.18371 3355.95113) (5912.51912 3363.49898)))
("SF_PLANTING" 0 ((5882.35294 3235.29412) (5897.43563 3235.29412)))
("SF_PLANTING" 0 ((5884.23857 3589.74333) (5904.97738 3588.68699) (5923.67670 3581.01131) (5927.60181 3574.66063)))
("SF_SOLAR" 0 ((5886.12342 7926.09355) (5886.12342 7914.78133)))
("SF_ARCHITECTURE" 0 ((5886.12342 5177.22432) (5893.66516 5177.22432)))
("SF_PLANTING" 0 ((5886.12342 3491.70464) (5882.50758 3499.25249) (5886.12342 3510.55781)))
("SF_PLANTING" 0 ((5886.12342 950.22624) (5900.00271 938.75939) (5902.40475 923.83688) (5908.74785 916.28959)))
("SF_PLANTING" 0 ((5886.12342 950.22624) (5904.97738 984.16290)))
("SF_ARCHITECTURE" 0 ((5889.89468 5045.24887) (5923.83133 5040.42229) (5935.14355 5030.16550)))
("SF_PLANTING" 0 ((5901.20690 3996.98382) (5891.09876 3985.67161) (5889.89468 3974.35939)))
("SF_PLANTING" 0 ((5931.37229 3898.94378) (5923.82443 3896.37115) (5904.97738 3902.56686) (5889.89468 3902.71493)))
("SF_SOLAR" 0 ((6085.97285 8103.31833) (5923.83133 8099.55407) (5893.66516 8107.08891)))
("SF_SOLAR" 0 ((5893.66516 7948.71799) (5897.43563 7960.03020)))
("SF_MASONRY_AND_ARCH" 0 ((5901.20690 2956.25939) (5897.43563 3024.13247) (5901.20068 3186.27477) (5897.43563
3235.29412)))
("SF_PLANTING" 0 ((5938.91403 3239.06459) (5931.36606 3242.68812) (5908.74785 3242.68122) (5897.43563 3235.29412)))
("SF_PLANTING" 0 ((5897.43563 369.53337) (5950.22624 365.76075)))
("SF_SOLAR" 0 ((5908.74785 8118.40113) (5901.20690 8133.48416)))
("SF_MASONRY_AND_ARCH" 0 ((5901.20690 2956.25939) (5938.91403 2960.03043)))
("SF_PLANTING" 0 ((5904.97738 984.16290) (5937.02839 980.39310)))
("SF_SOLAR" 0 ((5908.74785 7914.78133) (5908.74785 7926.09355)))
("SF_PLANTING" 0 ((5908.74785 3744.34389) (5927.60181 3763.19717)))
("SF_PLANTING" 0 ((5908.74785 3672.69943) (5931.52081 3623.68066) (5942.68450 3613.56572) (5957.76799 3608.59729)))
("SF_PLANTING" 0 ((5908.74785 3510.55781) (5908.74785 3521.87002)))
("SF_PLANTING" 0 ((5938.91403 916.28959) (5908.74785 916.28959)))
("SF_PLANTING" 0 ((5908.74785 233.78676) (5920.06007 230.16256) (5953.99672 230.16946) (5972.85068 241.32636)))
("SF_PLANTING" 0 ((5908.74785 233.78676) (5912.51912 252.63857)))
("SF_PLANTING" 0 ((5927.60181 3706.63609) (5912.51912 3710.40724)))
("SF_PLANTING" 0 ((5916.28959 3555.80667) (5927.60181 3574.66063)))
("SF_ARCHITECTURE" 0 ((5920.06007 5165.91210) (5935.14355 5165.91210)))
("SF_PLANTING" 0 ((5920.06007 3853.69491) (5935.14355 3863.95102) (5953.99672 3864.85928) (5972.85068 3860.03247)
(5984.16290 3851.12885) (6010.55158 3844.95622) (6018.09955 3838.61278)))
("SF_SOLAR" 0 ((6123.67998 8061.84005) (5923.83133 8061.84005)))
("SF_PLANTING" 0 ((5923.83133 448.71889) (5931.37229 441.17647)))
("SF_PLANTING" 0 ((5923.83133 448.71889) (5912.51912 447.51403) (5902.55939 437.40667) (5906.17534 422.32183)
(5920.06007 411.16493) (5946.45577 414.78224)))
("SF_PLANTING" 0 ((5923.83133 448.71889) (5931.37229 460.03111) (5935.14355 460.03111)))
("SF_PLANTING" 0 ((5923.83133 328.05430) (5923.83133 339.36652)))
("SF_PLANTING" 0 ((5969.08020 294.11765) (5935.14355 323.22738) (5923.83133 328.05430)))
("SF_PLANTING" 0 ((5969.08020 267.72342) (5927.75645 272.69808) (5923.83133 282.80543)))
("SF_ARCHITECTURE" 0 ((5927.60181 5018.85328) (5931.52692 5012.50328) (5942.68450 5008.59152) (5965.30894 5007.54106)))
("SF_ARCHITECTURE" 0 ((5927.60181 5018.85328) (5931.37229 5030.16550) (5935.14355 5030.16550)))
("SF_PLANTING" 0 ((5927.60181 3770.73948) (5927.60181 3763.19717)))
("SF_PLANTING" 0 ((5927.60181 3770.73948) (5942.68450 3774.50939)))
("SF_PLANTING" 0 ((5927.60181 3763.19717) (5933.94559 3755.64989) (5939.97036 3725.49061) (5946.45577 3714.17839)))
("SF_PLANTING" 0 ((5927.60181 3706.63609) (5927.60181 3691.55396)))
("SF_PLANTING" 0 ((5927.60181 3706.63609) (5946.45577 3714.17839)))
("SF_PLANTING" 0 ((5938.91403 3574.66063) (5927.60181 3574.66063)))
("SF_SOLAR" 0 ((5931.37229 8137.25498) (5931.37229 8118.40113)))
("SF_SOLAR" 0 ((5931.37229 8076.92308) (5931.37229 8088.23529)))
("SF_SOLAR" 0 ((5931.37229 7929.86425) (5938.91403 7929.86425)))
("SF_PLANTING" 0 ((5980.39242 3921.56821) (5961.53846 3932.73258) (5931.37229 3925.33937)))
("SF_MASONRY_AND_ARCH" 0 ((5931.37229 2616.89265) (5942.68450 2631.97590) (5961.53846 2631.97590) (6074.66063
2631.97590) (6097.28507 2631.97590) (6263.19785 2631.97590) (6282.05102 2631.97590) (6312.21719 2631.97590) (6346.15385
2631.97590) (6357.46606 2631.97590) (6425.33937 2635.74661)))
("SF_ARCHITECTURE" 0 ((5969.08020 5022.62443) (5957.76799 5030.01154) (5935.14355 5030.16550)))
("SF_PLANTING" 0 ((5935.14355 3503.01686) (5957.76799 3480.39242)))
("SF_PLANTING" 0 ((5935.14355 1006.78733) (5937.02839 980.39310)))
("SF_PLANTING" 0 ((5935.14355 1006.78733) (5924.88077 1014.33462) (5917.64842 1029.41176) (5942.68450 1059.57862)))
("SF_PLANTING" 0 ((5935.14355 1006.78733) (5952.79265 1029.41176) (5950.22624 1052.03620)))
("SF_PLANTING" 0 ((5935.14355 460.03111) (5953.84208 444.94627) (5960.12025 429.86425) (5946.45577 414.78224)))
("SF_PLANTING" 0 ((5938.91403 467.57070) (5935.14355 460.03111)))
("SF_PLANTING" 0 ((5978.50679 980.39310) (5937.02839 980.39310)))
("SF_PLANTING" 0 ((5942.68450 927.60181) (5937.02839 980.39310)))
("SF_PLANTING" 0 ((5938.91403 3676.47059) (5953.99672 3658.82115) (5995.47511 3657.61731)))
("SF_PLANTING" 0 ((5938.91403 3574.66063) (5961.37692 3548.26572) (5957.61335 3538.15758) (5946.45577 3536.95351)))
("SF_PLANTING" 0 ((5938.91403 3574.66063) (5957.76799 3608.59729)))
("SF_PLANTING" 0 ((5969.08020 3239.06459) (5938.91403 3239.06459)))
("SF_MASONRY_AND_ARCH" 0 ((5938.91403 3239.06459) (5938.90781 3012.82025) (5935.14355 2990.19581) (5938.91403
2960.03043)))
("SF_MASONRY_AND_ARCH" 0 ((5938.91403 2960.03043) (5969.08020 2960.03043)))
("SF_MASONRY_AND_ARCH" 0 ((5942.68450 2537.70713) (5938.91403 2522.62443)))
("SF_MASONRY_AND_ARCH" 0 ((6293.36324 2526.39491) (5938.91403 2522.62443)))
("SF_PLANTING" 0 ((5938.91403 916.28959) (5942.83914 908.88948) (5957.76799 901.35532) (5980.39242 902.41097)
(5991.70464 912.51980)))
("SF_PLANTING" 0 ((5942.68450 927.60181) (5938.91403 916.28959)))
("SF_PLANTING" 0 ((6055.80667 516.59219) (5950.22624 516.58529) (5938.91403 512.81957)))
("SF_PLANTING" 0 ((5942.68450 4030.92048) (5924.88767 4042.38054) (5920.20860 4053.54491) (5921.26425 4064.85023)
(5935.14355 4074.96459) (5952.94729 4064.85023) (5966.36538 4034.69038) (5999.24559 3989.44152)))
("SF_PLANTING" 0 ((5980.39242 3755.65611) (5942.68450 3774.50939)))
("SF_PLANTING" 0 ((5957.76799 3819.75826) (5942.68450 3774.50939)))
("SF_PLANTING" 0 ((5942.68450 927.60181) (5976.62115 935.14423)))
("SF_PLANTING" 0 ((5946.45577 3959.27602) (5965.30894 3966.81708)))
("SF_PLANTING" 0 ((5965.30894 3714.17839) (5946.45577 3714.17839)))
("SF_PLANTING" 0 ((5950.22624 365.76075) (5953.84898 392.15781) (5946.45577 414.78224)))
("SF_SOLAR" 0 ((6127.45124 8042.98643) (6085.97285 8039.22217) (6010.55781 8039.36369) (5995.47511 8042.97330)
(5972.85068 8039.22229) (5957.77421 8042.62443) (5950.22624 8039.21561)))
("SF_PLANTING" 0 ((5950.22624 3895.17387) (5961.53846 3896.83790) (5987.93337 3887.78654) (5999.24559 3891.40271)))
("SF_PLANTING" 0 ((5961.53846 3431.37229) (5950.22624 3442.68450)))
("SF_PLANTING" 0 ((5950.22624 365.76075) (5965.45747 343.28473) (5987.93337 331.82410)))
("SF_SOLAR" 0 ((5953.99672 8118.40113) (5953.99672 8133.48416)))
("SF_SOLAR" 0 ((5953.99672 8088.23529) (5953.99672 8069.38167)))
("SF_ARCHITECTURE" 0 ((5957.76799 5154.59989) (5972.85068 5154.59989)))
("SF_PLANTING" 0 ((5995.47511 3657.61731) (5980.24389 3619.91572) (5957.76799 3608.59729)))
("SF_PLANTING" 0 ((5961.53846 1108.59729) (5961.68620 1085.97975) (5965.30894 1078.43043)))
("SF_SOLAR" 0 ((5965.30894 8009.04977) (5976.62115 8005.42704) (6014.32907 8005.28552) (6116.13903 8012.80747)
(6142.53394 8005.43371) (6157.61663 8012.82059)))
("SF_ARCHITECTURE" 0 ((5995.47511 4996.22885) (5969.23484 5001.19106) (5965.30894 5007.54106)))
("SF_ARCHITECTURE" 0 ((5969.08020 5022.62443) (5965.30894 5018.85328) (5965.30894 5007.54106)))
("SF_PLANTING" 0 ((5965.30894 3714.17839) (5966.50690 3702.86550) (5995.47511 3657.61731)))
("SF_PLANTING" 0 ((5965.30894 3714.17839) (5980.39242 3729.26052)))
("SF_SOLAR" 0 ((5969.08020 7843.13722) (6006.78733 7843.13722)))
("SF_ARCHITECTURE" 0 ((5969.08020 5022.62443) (5995.46821 5017.65600) (6003.01686 5011.31222)))
("SF_MASONRY_AND_ARCH" 0 ((5969.08020 3239.06459) (5965.31584 3220.21143) (5969.07398 3197.58699) (5969.08020
2960.03043)))
("SF_PLANTING" 0 ((5969.08020 3239.06459) (5984.16290 3242.83586) (6006.78733 3239.06459)))
("SF_MASONRY_AND_ARCH" 0 ((5969.08020 2960.03043) (6003.01686 2960.03043)))
("SF_PLANTING" 0 ((5969.08020 294.11765) (5969.08020 267.72342)))
("SF_PLANTING" 0 ((5969.08020 294.11765) (5991.70464 301.66007)))
("SF_PLANTING" 0 ((5969.08020 267.72342) (5972.85068 241.32636)))
("SF_PLANTING" 0 ((5972.85068 241.32636) (6036.95351 241.32636)))
("SF_SOLAR" 0 ((5976.62115 8118.40113) (5976.62115 8125.94276)))
("SF_SOLAR" 0 ((5976.62115 8069.38167) (5976.62115 8088.23529)))
("SF_SOLAR" 0 ((5984.16290 7892.15690) (5986.87081 7873.30317) (5976.62115 7858.22025)))
("SF_PLANTING" 0 ((5976.62115 935.14423) (5991.70464 912.51980)))
("SF_PLANTING" 0 ((5978.50679 980.39310) (5976.62115 935.14423)))
("SF_PLANTING" 0 ((5978.50679 980.39310) (6006.78733 980.39310)))
("SF_PLANTING" 0 ((5991.70464 1033.18156) (5984.30441 1029.25713) (5977.67760 1018.09955) (5978.50679 980.39310)))
("SF_PLANTING" 0 ((5980.39242 3755.65611) (5980.39242 3729.26052)))
("SF_PLANTING" 0 ((5980.39242 3755.65611) (6010.55781 3770.73948)))
("SF_PLANTING" 0 ((6048.26572 3706.63609) (6036.95351 3716.89287) (6018.09955 3724.44016) (5980.39242 3729.26052)))
("SF_SOLAR" 0 ((6010.55781 7903.46912) (5984.16290 7892.15690)))
("SF_PLANTING" 0 ((5991.70464 309.19966) (5987.93337 331.82410)))
("SF_PLANTING" 0 ((6010.55781 392.15781) (5996.53145 358.22115) (5994.27715 339.37342) (5987.93337 331.82410)))
("SF_PLANTING" 0 ((5991.70464 1033.18156) (6010.55781 1014.32975)))
("SF_PLANTING" 0 ((5991.70464 1033.18156) (5996.67229 1052.02930) (6003.01686 1059.57862)))
("SF_PLANTING" 0 ((6029.41176 912.51980) (5991.70464 912.51980)))
("SF_PLANTING" 0 ((5991.70464 309.19966) (5991.70464 301.66007)))
("SF_PLANTING" 0 ((5991.70464 309.19966) (6014.32907 320.36414) (6040.72398 320.51188)))
("SF_PLANTING" 0 ((6021.87002 282.80543) (5991.70464 301.66007)))
("SF_SOLAR" 0 ((5995.47511 7971.34231) (6168.92885 7971.34887) (6180.24106 7975.11312)))
("SF_ARCHITECTURE" 0 ((6006.78733 5143.28767) (5995.47511 5143.28767)))
("SF_ARCHITECTURE" 0 ((5995.47511 4996.22885) (5999.40023 4989.87885) (6010.55781 4985.96708) (6036.95351 4984.91663)))
("SF_ARCHITECTURE" 0 ((5995.47511 4996.22885) (6003.01686 5011.31222)))
("SF_PLANTING" 0 ((5995.47511 3657.61731) (6018.09955 3657.61731)))
("SF_SOLAR" 0 ((5999.24559 8118.40113) (5999.24559 8133.48416)))
("SF_SOLAR" 0 ((5999.24559 8088.23529) (6003.01686 8069.38167)))
("SF_SOLAR" 0 ((5999.24559 8035.44502) (5999.24559 8020.36199)))
("SF_SOLAR" 0 ((5999.24559 7990.19615) (6003.01686 7978.88394)))
("SF_SOLAR" 0 ((5999.24559 7873.30317) (6006.63959 7869.37783) (6021.87692 7844.34152) (6052.03620 7843.13722)))
("SF_PLANTING" 0 ((5999.24559 3891.40271) (5999.24559 3902.71493)))
("SF_PLANTING" 0 ((5999.24559 3891.40271) (6036.95351 3865.00713)))
("SF_ARCHITECTURE" 0 ((6040.72398 4996.22885) (6033.17602 5006.33722) (6003.01686 5011.31222)))
("SF_MASONRY_AND_ARCH" 0 ((6036.95351 2960.03043) (6021.87002 2956.25916) (6003.01686 2960.03043)))
("SF_MASONRY_AND_ARCH" 0 ((6006.78733 3239.06459) (6003.01686 2960.03043)))
("SF_PLANTING" 0 ((6006.78733 3239.06459) (6021.87002 3242.83586) (6040.72398 3239.06459)))
("SF_PLANTING" 0 ((6006.78733 980.39310) (6033.18224 969.08088)))
("SF_PLANTING" 0 ((6006.78733 980.39310) (6010.55781 1014.32975)))
("SF_SOLAR" 0 ((6010.55781 7903.46912) (6036.95351 7899.69842) (6059.57794 7903.46256) (6191.55328 7903.46256)
(6214.17771 7899.69842) (6236.80215 7903.46256) (6289.59276 7903.32104) (6308.44672 7899.69842) (6331.07115 7903.46256)
(6561.08597 7903.46256) (6576.16867 7899.85294) (6595.02262 7903.46256) (6768.47636 7903.32104) (6806.18428 7892.00226)
(6836.34966 7850.67873)))
("SF_SOLAR" 0 ((6010.55781 7903.46912) (6009.50147 7922.32274) (6001.96041 7937.40577) (5955.04627 7997.73756)
(5843.59559 8156.10860) (5815.67760 8186.27443) (5811.01154 8201.35079) (5814.63428 8207.69457) (5844.64581 8212.66301)
(5867.27025 8208.91199) (5897.43563 8212.66957) (5920.06007 8208.89898) (6025.64129 8208.89898) (6040.72398 8208.89898)
(6055.80667 8208.89898) (6244.34389 8208.89898) (6315.98767 8212.66312) (6334.84163 8208.90543) (6602.56437 8208.75079)
(6628.95928 8198.79106) (6651.58371 8208.89231) (7315.23405 8208.75079) (7326.54627 8204.07195) (7340.57262 8190.04525)
(7436.95362 8039.21561) (7521.57500 7922.32274) (7538.76357 7892.15690) (7560.33156 7869.68710) (7571.64378 7865.76821)
(7699.85011 7865.61357) (7722.17070 7850.67873) (7721.26968 7779.04129) (7714.92523 7772.69751) (7696.07749
7767.72251)))
("SF_PLANTING" 0 ((6010.55781 3770.73948) (6029.41176 3763.34559) (6059.57794 3759.42726)))
("SF_PLANTING" 0 ((6010.55781 3770.73948) (6010.70554 3808.44604) (6018.09955 3838.61278)))
("SF_PLANTING" 0 ((6093.51459 1048.26640) (6082.20238 1058.37998) (6070.89016 1062.29898) (6052.18394 1062.14355)
(6021.64977 1014.69774) (6010.55781 1014.32975)))
("SF_SOLAR" 0 ((6014.32907 7937.40577) (6112.36776 7937.41233) (6134.99219 7941.17647) (6199.09502 7937.40577)))
("SF_PLANTING" 0 ((6036.95351 3849.92500) (6025.64751 3839.81663) (6018.09955 3838.61278)))
("SF_PLANTING" 0 ((6025.64129 3646.30509) (6018.09955 3657.61731)))
("SF_PLANTING" 0 ((6018.09955 3657.61731) (6044.33982 3684.16007) (6048.26572 3695.32387)))
("SF_SOLAR" 0 ((6021.87002 8118.40113) (6021.87002 8125.94276)))
("SF_SOLAR" 0 ((6021.87002 8020.36199) (6021.87002 8031.67421)))
("SF_PLANTING" 0 ((6063.34842 3985.67161) (6062.29898 4008.29604) (6036.80498 4071.19367) (6025.64751 4071.19367)
(6017.21097 4061.08597) (6015.53314 4053.54491) (6021.87002 4038.46154)))
("SF_SOLAR" 0 ((6025.64129 7960.03020) (6025.64129 7948.71799)))
("SF_PLANTING" 0 ((6044.49446 3936.65158) (6025.64129 3921.56821)))
("SF_PLANTING" 0 ((6044.49446 3597.28507) (6036.94661 3598.48925) (6026.84536 3608.59729) (6025.64129 3646.30509)))
("SF_PLANTING" 0 ((6025.64129 3646.30509) (6063.34842 3646.45294) (6082.20238 3653.69808) (6097.28507 3653.99423)
(6112.36776 3658.81459) (6123.67998 3668.92952)))
("SF_PLANTING" 0 ((6044.49446 935.14423) (6040.72398 931.37161) (6029.41176 931.37161)))
("SF_PLANTING" 0 ((6029.41176 931.37161) (6029.41176 912.51980)))
("SF_PLANTING" 0 ((6029.41176 931.37161) (6033.18224 969.08088)))
("SF_PLANTING" 0 ((6029.41176 912.51980) (6048.26572 901.35532) (6070.88326 901.35464) (6078.43111 904.97738)))
("SF_ARCHITECTURE" 0 ((6033.18224 5131.97545) (6052.03620 5131.97545)))
("SF_PLANTING" 0 ((6033.18224 969.08088) (6052.03620 969.08088)))
("SF_ARCHITECTURE" 0 ((6036.95351 4984.91663) (6040.87862 4978.57319) (6074.66063 4973.60441)))
("SF_ARCHITECTURE" 0 ((6040.72398 4996.22885) (6036.95351 4984.91663)))
("SF_PLANTING" 0 ((6036.95351 3849.92500) (6036.95351 3865.00713)))
("SF_PLANTING" 0 ((6067.11889 3917.79830) (6062.29208 3902.71493) (6036.95351 3865.00713)))
("SF_PLANTING" 0 ((6127.45124 3876.31934) (6085.97285 3858.52274) (6036.95351 3849.92500)))
("SF_MASONRY_AND_ARCH" 0 ((6036.95351 2960.03043) (6067.11889 2960.03043)))
("SF_MASONRY_AND_ARCH" 0 ((6036.95351 2960.03043) (6036.95973 3084.46482) (6040.72398 3107.08925) (6040.71776
3193.81572) (6036.95973 3220.21143) (6040.72398 3239.06459)))
("SF_PLANTING" 0 ((6063.34842 411.00962) (6036.95351 414.78224)))
("SF_PLANTING" 0 ((6123.67998 237.55656) (6104.82681 230.16256) (6048.26572 233.94005) (6036.95351 241.32636)))
("SF_PLANTING" 0 ((6048.26572 279.03563) (6036.95351 241.32636)))
("SF_ARCHITECTURE" 0 ((6040.72398 4996.22885) (6063.34219 4995.02500) (6069.83371 4988.68156) (6074.66063 4973.60441)))
("SF_PLANTING" 0 ((6078.43111 3239.06459) (6059.57794 3242.83586) (6040.72398 3239.06459)))
("SF_PLANTING" 0 ((6040.72398 320.51188) (6040.87240 297.88744) (6048.26572 279.03563)))
("SF_PLANTING" 0 ((6040.72398 320.51188) (6097.28507 328.05430)))
("SF_SOLAR" 0 ((6044.49446 8133.48416) (6044.49446 8118.40113)))
("SF_SOLAR" 0 ((6044.49446 8069.38167) (6044.49446 8080.69389)))
("SF_SOLAR" 0 ((6044.49446 8031.67421) (6044.49446 8020.36199)))
("SF_SOLAR" 0 ((6044.49446 7978.88394) (6044.49446 7990.19615)))
("SF_PLANTING" 0 ((6067.11889 3917.79830) (6044.49446 3936.65158)))
("SF_PLANTING" 0 ((6063.34842 3985.67161) (6044.49446 3980.70283) (6030.62285 3963.04717) (6044.49446 3936.65158)))
("SF_PLANTING" 0 ((6044.49446 3597.28507) (6044.49446 3589.74333)))
("SF_PLANTING" 0 ((6044.49446 3597.28507) (6070.89016 3601.05554)))
("SF_SOLAR" 0 ((6048.26572 7914.78133) (6048.26572 7926.09355)))
("SF_PLANTING" 0 ((6048.26572 3706.63609) (6048.26572 3695.32387)))
("SF_PLANTING" 0 ((6048.26572 3706.63609) (6054.60950 3714.18462) (6059.43020 3733.03167) (6059.57794 3759.42726)))
("SF_PLANTING" 0 ((6104.82681 3695.32387) (6048.26572 3695.32387)))
("SF_PLANTING" 0 ((6123.67998 252.63857) (6089.74333 270.44378) (6048.26572 279.03563)))
("SF_PLANTING" 0 ((6082.20238 938.91403) (6070.88326 957.76109) (6052.03620 969.08088)))
("SF_PLANTING" 0 ((6093.51459 1003.01753) (6082.20238 1006.49118) (6063.49683 998.18925) (6052.03620 969.08088)))
("SF_PLANTING" 0 ((6067.11889 426.09446) (6065.91482 433.64163) (6052.03620 448.71889)))
("SF_ARCHITECTURE" 0 ((6059.57794 5124.43439) (6202.86550 5068.92308) (6236.80215 5064.10215)))
("SF_PLANTING" 0 ((6059.57794 4121.41821) (6083.40023 4057.46324) (6108.59729 4042.23269)))
("SF_PLANTING" 0 ((6157.61663 3819.75826) (6146.30441 3822.17749) (6134.99219 3813.42138) (6112.36776 3807.24876)
(6059.57794 3759.42726)))
("SF_PLANTING" 0 ((6102.94118 3964.93213) (6063.34842 3985.67161)))
("SF_PLANTING" 0 ((6063.34842 411.00962) (6071.04480 388.53360) (6082.20238 381.90124) (6093.51459 380.84559)))
("SF_PLANTING" 0 ((6067.11889 426.09446) (6063.34842 411.00962)))
("SF_SOLAR" 0 ((6078.43111 8141.02557) (6068.32308 8148.57376) (6067.11889 8163.65000)))
("SF_SOLAR" 0 ((6101.05554 8163.65000) (6082.20238 8167.41414) (6067.11889 8163.65000)))
("SF_SOLAR" 0 ((6067.11889 8020.36199) (6067.11889 8031.67421)))
("SF_SOLAR" 0 ((6067.11889 7993.96674) (6067.11889 7978.88394)))
("SF_SOLAR" 0 ((6067.11889 7963.80090) (6067.11889 7948.71799)))
("SF_PLANTING" 0 ((6101.05554 3929.11052) (6082.20238 3918.85441) (6067.11889 3917.79830)))
("SF_PLANTING" 0 ((6067.11889 3612.36776) (6070.89016 3601.05554)))
("SF_MASONRY_AND_ARCH" 0 ((6067.11889 2960.03043) (6085.97285 2960.03043)))
("SF_MASONRY_AND_ARCH" 0 ((6078.43111 3001.50803) (6071.04480 2993.96018) (6067.11889 2960.03043)))
("SF_PLANTING" 0 ((6067.11889 426.09446) (6082.20238 426.09446)))
("SF_SOLAR" 0 ((6070.89016 8069.38167) (6070.89016 8080.69389)))
("SF_PLANTING" 0 ((6085.97285 3578.43111) (6081.14593 3593.50769) (6070.89016 3601.05554)))
("SF_ARCHITECTURE" 0 ((6074.66063 4973.60441) (6089.74333 4972.54898) (6104.67217 4965.00667) (6108.59038 4954.75113)
(6108.60351 4177.97930) (6112.07161 4162.89593) (6108.60351 4147.81256) (6108.59729 4042.23269)))
("SF_SOLAR" 0 ((6078.43111 8141.02557) (6097.28507 8137.25498)))
("SF_SOLAR" 0 ((6078.43111 8141.02557) (6079.63529 8129.71335) (6123.67998 8061.84005)))
("SF_MASONRY_AND_ARCH" 0 ((6078.43111 3001.50803) (6078.43111 3239.06459)))
("SF_PLANTING" 0 ((6078.43111 3239.06459) (6097.28507 3242.83586) (6119.90950 3239.06459)))
("SF_MASONRY_AND_ARCH" 0 ((6078.43111 3001.50803) (6085.81821 2990.19581) (6085.97285 2960.03043)))
("SF_MASONRY_AND_ARCH" 0 ((6078.43111 2100.30192) (6082.35701 2093.95814) (6116.13903 2088.98971)))
("SF_MASONRY_AND_ARCH" 0 ((6078.43111 2100.30192) (6088.53925 2107.84287) (6089.74333 2115.38462)))
("SF_PLANTING" 0 ((6078.43111 904.97738) (6082.20238 938.91403)))
("SF_PLANTING" 0 ((6078.43111 904.97738) (6112.36776 905.13201) (6127.45124 916.28959)))
("SF_PLANTING" 0 ((6123.67998 938.91403) (6082.20238 938.91403)))
("SF_PLANTING" 0 ((6082.20238 426.09446) (6093.51459 388.38518)))
("SF_PLANTING" 0 ((6082.20238 426.09446) (6096.22873 448.71889) (6101.05554 471.34333)))
("SF_MASONRY_AND_ARCH" 0 ((6085.97285 2960.03043) (6119.90950 2960.03043)))
("SF_SOLAR" 0 ((6089.74333 8031.67421) (6089.74333 8020.36199)))
("SF_SOLAR" 0 ((6089.74333 7978.88394) (6089.74333 7990.19615)))
("SF_MASONRY_AND_ARCH" 0 ((6089.74333 2115.38462) (6108.59106 2112.50894) (6119.90950 2100.30192)))
("SF_PLANTING" 0 ((6093.51459 380.84559) (6093.51459 388.38518)))
("SF_PLANTING" 0 ((6131.22172 411.00962) (6120.59717 391.47636) (6093.51459 388.38518)))
("SF_PLANTING" 0 ((6093.51459 380.84559) (6097.43971 354.44853) (6104.82681 339.36652)))
("SF_SOLAR" 0 ((6097.28507 8129.71335) (6097.28507 8137.25498)))
("SF_SOLAR" 0 ((6104.82681 8144.79638) (6097.28507 8137.25498)))
("SF_PLANTING" 0 ((6097.28507 1146.30373) (6108.59729 1157.46267) (6127.45124 1153.84615)))
("SF_PLANTING" 0 ((6123.67998 252.63857) (6131.06086 263.95079) (6126.25328 282.80543) (6109.65362 301.66007)
(6097.28507 328.05430)))
("SF_PLANTING" 0 ((6104.82681 339.36652) (6097.28507 328.05430)))
("SF_SOLAR" 0 ((6101.05554 8163.65000) (6104.82681 8144.79638)))
("SF_SOLAR" 0 ((6101.05554 8163.65000) (6338.61210 8163.65656) (6357.46606 8171.19163) (6365.00781 8167.42081)
(6380.09050 8166.22319) (6391.40271 8159.87941)))
("SF_PLANTING" 0 ((6119.90950 3921.56821) (6101.05554 3929.11052)))
("SF_PLANTING" 0 ((6101.05554 3929.11052) (6102.94118 3964.93213)))
("SF_PLANTING" 0 ((6101.05554 3431.37229) (6112.36776 3446.45577)))
("SF_PLANTING" 0 ((6101.05554 516.59219) (6119.90950 520.36199)))
("SF_PLANTING" 0 ((6102.94118 3964.93213) (6108.44955 3981.90045) (6108.59729 4012.06595)))
("SF_PLANTING" 0 ((6157.61686 3966.81708) (6102.94118 3964.93213)))
("SF_SOLAR" 0 ((6112.36776 8141.02557) (6104.82681 8144.79638)))
("SF_PLANTING" 0 ((6119.90950 3687.78281) (6104.82681 3695.32387)))
("SF_PLANTING" 0 ((6127.45124 3763.19717) (6109.65362 3733.03167) (6104.82681 3695.32387)))
("SF_PLANTING" 0 ((6116.13903 339.36652) (6104.82681 339.36652)))
("SF_PLANTING" 0 ((6108.59729 4012.06595) (6108.59729 4042.23269)))
("SF_PLANTING" 0 ((6157.61686 4012.06595) (6108.59729 4012.06595)))
("SF_SOLAR" 0 ((6112.36776 8141.02557) (6266.96833 8140.87093) (6274.36154 8137.10023) (6285.82229 8118.40113)))
("SF_SOLAR" 0 ((6172.70011 8058.06946) (6151.12511 8076.92308) (6117.18846 8125.94276) (6112.36776 8141.02557)))
("SF_SOLAR" 0 ((6116.13903 8024.13281) (6112.36776 8031.67421)))
("SF_SOLAR" 0 ((6112.36776 7993.96674) (6112.36776 7982.65452)))
("SF_SOLAR" 0 ((6112.36776 7963.80090) (6112.36776 7952.48869)))
("SF_PLANTING" 0 ((6112.36776 3446.45577) (6116.13903 3469.08020)))
("SF_PLANTING" 0 ((6112.36776 3446.45577) (6138.76346 3454.15136) (6148.87149 3465.30894) (6150.07568 3476.62115)))
("SF_MASONRY_AND_ARCH" 0 ((6116.13903 2088.98971) (6120.06414 2082.63903) (6138.76346 2077.67749)))
("SF_MASONRY_AND_ARCH" 0 ((6116.13903 2088.98971) (6119.90950 2100.30192)))
("SF_PLANTING" 0 ((6165.15837 237.55656) (6167.73100 248.86878) (6160.19683 279.03563) (6133.94276 320.51188)
(6116.13903 339.36652)))
("SF_PLANTING" 0 ((6116.13903 339.36652) (6123.68688 345.71029) (6161.38790 354.44853)))
("SF_PLANTING" 0 ((6127.45124 3876.31934) (6119.90950 3921.56821)))
("SF_PLANTING" 0 ((6119.90950 3921.56821) (6161.38790 3929.11052)))
("SF_PLANTING" 0 ((6119.90950 3687.78281) (6123.67998 3668.92952)))
("SF_PLANTING" 0 ((6142.53394 3733.03167) (6141.33597 3714.17839) (6119.90950 3687.78281)))
("SF_PLANTING" 0 ((6155.73179 3239.06459) (6119.90950 3239.06459)))
("SF_MASONRY_AND_ARCH" 0 ((6119.90950 2960.03043) (6119.90328 3178.73303) (6116.13903 3201.35747) (6116.28676
3231.51674) (6119.90950 3239.06459)))
("SF_MASONRY_AND_ARCH" 0 ((6119.90950 2960.03043) (6153.84615 2960.03043)))
("SF_MASONRY_AND_ARCH" 0 ((6138.76346 2077.67749) (6134.83756 2092.61176) (6119.90950 2100.30192)))
("SF_PLANTING" 0 ((6123.67998 938.91403) (6119.90950 991.70532)))
("SF_PLANTING" 0 ((6119.90950 991.70532) (6124.88416 1025.64197) (6134.83756 1040.72398) (6134.99219 1078.43043)))
("SF_PLANTING" 0 ((6180.24106 995.47511) (6119.90950 991.70532)))
("SF_SOLAR" 0 ((6123.67998 8061.84005) (6145.25498 8035.44502) (6157.61663 8012.82059)))
("SF_PLANTING" 0 ((6123.67998 3668.92952) (6138.76346 3668.92952)))
("SF_PLANTING" 0 ((6123.67998 938.91403) (6127.45124 916.28959)))
("SF_PLANTING" 0 ((6123.67998 252.63857) (6123.67998 237.55656)))
("SF_PLANTING" 0 ((6165.15837 237.55656) (6123.67998 237.55656)))
("SF_PLANTING" 0 ((6127.45124 3876.31934) (6150.07568 3871.35124) (6176.47059 3850.98043) (6199.09502 3846.15385)))
("SF_PLANTING" 0 ((6131.22172 3352.18676) (6127.45124 3363.49898)))
("SF_PLANTING" 0 ((6131.22172 3352.18676) (6127.45124 3340.87455)))
("SF_PLANTING" 0 ((6138.76346 1153.84615) (6127.45124 1153.84615)))
("SF_PLANTING" 0 ((6127.45124 1153.84615) (6127.45124 1123.67930)))
("SF_PLANTING" 0 ((6138.76346 1123.67930) (6127.45124 1123.67930)))
("SF_PLANTING" 0 ((6134.99219 1078.43043) (6123.82851 1101.05486) (6127.45124 1123.67930)))
("SF_PLANTING" 0 ((6187.78281 916.28959) (6127.45124 916.28959)))
("SF_PLANTING" 0 ((6131.22172 3352.18676) (6146.30441 3353.24321) (6165.15837 3365.91765) (6176.47059 3363.49898)))
("SF_MASONRY_AND_ARCH" 0 ((6342.38337 2662.14152) (6251.88563 2662.14774) (6233.03167 2665.90588) (6210.40724
2662.14774) (6131.22172 2662.14152)))
("SF_PLANTING" 0 ((6131.22172 418.55204) (6131.22172 411.00962)))
("SF_PLANTING" 0 ((6131.22172 411.00962) (6138.62183 409.80622) (6148.88462 395.92760) (6161.38790 354.44853)))
("SF_PLANTING" 0 ((6153.84615 1078.43043) (6134.99219 1078.43043)))
("SF_SOLAR" 0 ((6138.76346 8061.84005) (6142.53394 8073.15226)))
("SF_PLANTING" 0 ((6168.92885 3597.28507) (6142.53394 3598.48925) (6132.42590 3608.59729) (6138.76346 3668.92952)))
("SF_PLANTING" 0 ((6176.47059 3680.24174) (6138.76346 3668.92952)))
("SF_MASONRY_AND_ARCH" 0 ((6138.76346 2077.67749) (6138.75724 1919.30645) (6134.99219 1896.68201) (6134.99842
1206.63744) (6138.76346 1153.84615)))
("SF_PLANTING" 0 ((6138.76346 1153.84615) (6145.10656 1149.92104) (6146.14977 1142.53394) (6138.76346 1123.67930)))
("SF_PLANTING" 0 ((6138.76346 1123.67930) (6152.64197 1112.22002) (6157.61663 1097.28507)))
("SF_SOLAR" 0 ((6142.53394 7990.19615) (6142.53394 7982.65452)))
("SF_SOLAR" 0 ((6146.30441 8103.31833) (6180.24106 8099.55419) (6195.32455 8103.17025) (6372.54876 8107.08235)
(6387.63224 8099.54751)))
("SF_SOLAR" 0 ((6146.30441 7839.36652) (6225.48993 7839.36652)))
("SF_SOLAR" 0 ((6150.07568 8042.98643) (6153.84615 8054.29864)))
("SF_SOLAR" 0 ((6150.07568 7869.53247) (6168.92885 7869.53247)))
("SF_PLANTING" 0 ((6150.07568 3476.62115) (6135.14072 3485.21233) (6128.50758 3495.47511) (6132.27805 3529.41176)
(6138.91120 3541.02014) (6146.30441 3544.78382) (6153.84615 3543.29378) (6165.15837 3533.18224)))
("SF_PLANTING" 0 ((6187.78281 3495.47511) (6150.07568 3476.62115)))
("SF_MASONRY_AND_ARCH" 0 ((6153.84615 2960.03043) (6184.01233 2960.03043)))
("SF_MASONRY_AND_ARCH" 0 ((6155.73179 3239.06459) (6150.08190 3178.73303) (6150.08190 3024.13247) (6153.84615
2960.03043)))
("SF_PLANTING" 0 ((6153.84615 1078.43043) (6167.87251 1063.34219) (6176.47059 1040.72398)))
("SF_PLANTING" 0 ((6153.84615 1078.43043) (6157.61663 1097.28507)))
("SF_PLANTING" 0 ((6155.73179 3239.06459) (6158.67308 3276.77251) (6173.75645 3306.78326) (6191.55328 3314.47964)))
("SF_PLANTING" 0 ((6184.01233 3239.06482) (6155.73179 3239.06459)))
("SF_SOLAR" 0 ((6157.61663 8118.40113) (6157.61663 8129.71335)))
("SF_SOLAR" 0 ((6157.61663 8012.82059) (6167.87319 8001.50826) (6180.24106 7975.11312)))
("SF_SOLAR" 0 ((6161.38790 7952.48869) (6157.61663 7963.80090)))
("SF_MASONRY_AND_ARCH" 0 ((6184.01233 1184.01301) (6184.00611 2043.74084) (6179.03699 2104.06550) (6172.69321
2110.40995) (6157.61663 2111.61414)))
("SF_PLANTING" 0 ((6187.78281 1101.05486) (6157.61663 1097.28507)))
("SF_PLANTING" 0 ((6157.61686 4012.06595) (6157.61686 4027.14932)))
("SF_PLANTING" 0 ((6229.26120 4008.29604) (6202.86550 4026.09265) (6180.24106 4030.62398) (6157.61686 4027.14932)))
("SF_PLANTING" 0 ((6157.61686 3966.81708) (6157.61686 4004.51867) (6157.61686 4012.06595)))
("SF_PLANTING" 0 ((6157.61686 3966.81708) (6157.61686 3959.27602)))
("SF_PLANTING" 0 ((6161.38790 3929.11052) (6157.61686 3959.27602)))
("SF_PLANTING" 0 ((6157.61686 3959.27602) (6195.32455 3971.78586) (6229.26120 4008.29604)))
("SF_PLANTING" 0 ((6161.38790 3929.11052) (6161.38790 3921.56821)))
("SF_PLANTING" 0 ((6168.92885 961.53846) (6161.38790 957.76867)))
("SF_PLANTING" 0 ((6161.38790 516.59219) (6180.24106 516.59219)))
("SF_PLANTING" 0 ((6176.47059 350.67873) (6161.38790 354.44853)))
("SF_PLANTING" 0 ((6165.15837 237.55656) (6187.78281 230.16256) (6225.48993 233.78676)))
("SF_PLANTING" 0 ((6180.24106 3785.82161) (6168.92885 3812.21719)))
("SF_PLANTING" 0 ((6168.92885 3597.28507) (6176.62523 3578.58575) (6187.78281 3574.66063)))
("SF_PLANTING" 0 ((6168.92885 3597.28507) (6180.39570 3623.67376) (6202.86550 3634.99287)))
("SF_SOLAR" 0 ((6172.70011 8058.06946) (6173.89796 8046.75713) (6211.45667 7990.19615) (6258.22251 7933.63495)
(6259.42658 7914.78133)))
("SF_SOLAR" 0 ((6172.70011 8058.06946) (6365.00781 8058.07602) (6380.09050 8061.69208) (6421.56889 8061.84005)))
("SF_SOLAR" 0 ((6187.78281 8009.04977) (6172.70011 8009.04977)))
("SF_PLANTING" 0 ((6176.47059 3680.24174) (6202.86550 3661.38722)))
("SF_PLANTING" 0 ((6191.55328 3702.86618) (6177.67477 3691.55396) (6176.47059 3680.24174)))
("SF_PLANTING" 0 ((6180.24106 995.47511) (6176.47059 976.62048)))
("SF_PLANTING" 0 ((6225.48993 275.26301) (6211.60520 286.57523) (6181.29751 335.59672) (6176.47059 350.67873)))
("SF_PLANTING" 0 ((6202.86550 369.53337) (6195.31765 368.32851) (6176.47059 350.67873)))
("SF_SOLAR" 0 ((6180.24106 8118.40113) (6180.24106 8129.71335)))
("SF_SOLAR" 0 ((6180.24106 7975.11312) (6191.40554 7967.56505) (6229.26120 7914.78133)))
("SF_PLANTING" 0 ((6240.57342 1001.13122) (6214.17771 1010.40385) (6180.24106 995.47511)))
("SF_PLANTING" 0 ((6184.01233 3239.06482) (6191.55328 3239.06482)))
("SF_MASONRY_AND_ARCH" 0 ((6184.01233 3239.06482) (6184.16007 3156.11550) (6187.78281 3148.56686)))
("SF_MASONRY_AND_ARCH" 0 ((6184.01233 2960.03043) (6217.94898 2960.03043)))
("SF_MASONRY_AND_ARCH" 0 ((6187.78281 3073.15260) (6184.01855 3061.84038) (6184.01233 2960.03043)))
("SF_PLANTING" 0 ((6240.57342 1184.01301) (6184.01233 1184.01301)))
("SF_PLANTING" 0 ((6187.78281 1101.05486) (6184.16007 1112.36708) (6184.01233 1184.01301)))
("SF_SOLAR" 0 ((6187.78281 7914.78133) (6187.78281 7926.09355)))
("SF_PLANTING" 0 ((6206.63676 3857.46606) (6192.75747 3872.54943) (6187.78281 3887.63156)))
("SF_PLANTING" 0 ((6187.78281 3495.47511) (6195.32455 3484.16290)))
("SF_PLANTING" 0 ((6187.78281 3495.47511) (6196.52862 3533.17602) (6202.87240 3539.51980) (6214.17771 3540.72398)))
("SF_PLANTING" 0 ((6187.78281 3348.41629) (6191.55328 3314.47964)))
("SF_MASONRY_AND_ARCH" 0 ((6214.17771 3148.56686) (6187.78281 3148.56686)))
("SF_MASONRY_AND_ARCH" 0 ((6187.78281 3148.56686) (6180.24106 3107.08925) (6180.38880 3092.00577) (6187.78281
3073.15260)))
("SF_MASONRY_AND_ARCH" 0 ((6187.78281 3073.15260) (6210.40724 3073.15260)))
("SF_PLANTING" 0 ((6187.78281 1101.05486) (6195.32455 1097.28507)))
("SF_PLANTING" 0 ((6285.82229 916.28959) (6236.80215 901.20758) (6206.63676 902.25633) (6195.33077 906.17534)
(6187.78281 916.28959)))
("SF_PLANTING" 0 ((6240.57342 1001.13122) (6239.51697 987.93688) (6231.97534 972.85068) (6210.55498 950.22624)
(6187.78281 916.28959)))
("SF_SOLAR" 0 ((6195.32455 8069.38167) (6191.55328 8080.69389)))
("SF_PLANTING" 0 ((6191.55328 3702.86618) (6195.02828 3740.57274) (6191.55328 3766.96833)))
("SF_PLANTING" 0 ((6210.40724 3668.92952) (6201.66143 3691.55328) (6191.55328 3702.86618)))
("SF_PLANTING" 0 ((6191.55328 3239.06482) (6200.75973 3288.08473) (6197.89706 3306.93167) (6191.55328 3314.47964)))
("SF_PLANTING" 0 ((6191.55328 3239.06482) (6225.48993 3239.06482) (6248.11437 3239.06482)))
("SF_PLANTING" 0 ((6253.77048 3949.84876) (6206.63676 3926.40226) (6195.32455 3929.11052)))
("SF_PLANTING" 0 ((6217.94898 3484.16290) (6195.32455 3484.16290)))
("SF_PLANTING" 0 ((6214.17771 3393.66516) (6191.70792 3431.37229) (6195.32455 3484.16290)))
("SF_PLANTING" 0 ((6195.32455 1097.28507) (6221.71946 1097.13665) (6236.80215 1089.74265)))
("SF_PLANTING" 0 ((6195.32455 1089.74265) (6195.32455 1097.28507)))
("SF_PLANTING" 0 ((6233.03167 3797.13382) (6217.94898 3801.96165) (6207.83462 3812.21719) (6199.09502 3846.15385)))
("SF_PLANTING" 0 ((6206.63676 3857.46606) (6199.09502 3846.15385)))
("SF_SOLAR" 0 ((6202.86550 8118.40113) (6202.86550 8133.48416)))
("SF_PLANTING" 0 ((6202.86550 3661.38722) (6202.86550 3634.99287)))
("SF_PLANTING" 0 ((6210.40724 3668.92952) (6202.86550 3661.38722)))
("SF_PLANTING" 0 ((6214.17771 3604.82681) (6202.86550 3634.99287)))
("SF_PLANTING" 0 ((6202.86550 369.53337) (6218.09672 335.59672) (6229.26120 325.48790) (6244.34389 324.28450)))
("SF_PLANTING" 0 ((6202.86550 369.53337) (6203.92195 380.84559) (6214.17771 395.92760)))
("SF_PLANTING" 0 ((6229.26120 3861.23722) (6206.63676 3857.46606)))
("SF_PLANTING" 0 ((6216.06335 3386.12342) (6206.63676 3386.12342)))
("SF_SOLAR" 0 ((6210.40724 8012.82059) (6282.05102 8012.82715) (6315.98145 8016.74593) (6322.33145 8020.51663)
(6331.07115 8039.21561)))
("SF_PLANTING" 0 ((6210.40724 3668.92952) (6248.11437 3668.92952)))
("SF_MASONRY_AND_ARCH" 0 ((6217.94898 2960.03043) (6217.80124 3050.52817) (6210.40724 3073.15260)))
("SF_MASONRY_AND_ARCH" 0 ((6214.17771 3148.56686) (6217.80045 3092.00577) (6210.40724 3073.15260)))
("SF_MASONRY_AND_ARCH" 0 ((6334.84163 2398.19005) (6330.91652 2387.03247) (6323.52941 2383.26199) (6244.34389
2383.11357) (6210.40724 2386.87783)))
("SF_PLANTING" 0 ((6233.03167 4144.04265) (6214.17771 4147.81256)))
("SF_PLANTING" 0 ((6263.19785 3595.39943) (6229.26120 3604.67907) (6214.17771 3604.82681)))
("SF_PLANTING" 0 ((6214.17771 3540.72398) (6214.17771 3604.82681)))
("SF_PLANTING" 0 ((6214.17771 3540.72398) (6224.29208 3533.17602) (6229.26120 3514.32907)))
("SF_PLANTING" 0 ((6216.06335 3386.12342) (6221.71946 3389.89468) (6214.17771 3393.66516)))
("SF_PLANTING" 0 ((6216.06335 3386.12342) (6214.17771 3393.66516)))
("SF_MASONRY_AND_ARCH" 0 ((6214.17771 3148.56686) (6217.94898 3197.58699)))
("SF_PLANTING" 0 ((6216.06335 3386.12342) (6221.80023 3379.92805) (6233.03167 3382.35294)))
("SF_PLANTING" 0 ((6217.94898 3484.16290) (6231.82749 3465.30894) (6236.80215 3442.68450)))
("SF_PLANTING" 0 ((6217.94898 3484.16290) (6229.26120 3503.01686)))
("SF_MASONRY_AND_ARCH" 0 ((6251.88563 2960.03043) (6217.94898 2960.03043)))
("SF_PLANTING" 0 ((6244.34389 1136.87783) (6217.94898 1142.53394)))
("SF_SOLAR" 0 ((6233.03167 7854.44943) (6221.71946 7888.38609)))
("SF_PLANTING" 0 ((6229.26120 3880.09050) (6225.48993 3880.09050) (6221.71946 3887.63156)))
("SF_SOLAR" 0 ((6225.48993 8069.38167) (6225.48993 8084.46448)))
("SF_SOLAR" 0 ((6225.48993 8035.44502) (6225.48993 8024.13281)))
("SF_PLANTING" 0 ((6225.48993 275.26301) (6244.34389 275.26301)))
("SF_PLANTING" 0 ((6225.48993 275.26301) (6225.48993 233.78676)))
("SF_PLANTING" 0 ((6293.36324 241.32636) (6255.65611 233.93382) (6225.48993 233.78676)))
("SF_SOLAR" 0 ((6236.80215 7941.17647) (6229.26120 7941.17647)))
("SF_PLANTING" 0 ((6229.26120 4008.29604) (6236.80215 4008.29604)))
("SF_PLANTING" 0 ((6229.26120 3880.09050) (6229.26120 3861.23722)))
("SF_PLANTING" 0 ((6259.42658 3883.86165) (6229.26120 3880.09050)))
("SF_PLANTING" 0 ((6263.19785 3857.46606) (6236.80905 3857.61414) (6229.26120 3861.23722)))
("SF_PLANTING" 0 ((6233.03167 4144.04265) (6236.80215 4095.02262)))
("SF_PLANTING" 0 ((6240.57342 4151.58371) (6236.80215 4151.58371) (6233.03167 4144.04265)))
("SF_PLANTING" 0 ((6233.03167 3797.13382) (6233.17941 3770.73948) (6244.49163 3744.35011) (6255.65611 3736.80283)))
("SF_PLANTING" 0 ((6233.03167 3797.13382) (6285.82229 3800.90498)))
("SF_SOLAR" 0 ((6236.80215 8133.48416) (6244.34389 8118.40113)))
("SF_SOLAR" 0 ((6236.80215 8001.50837) (6244.35079 7997.88552) (6308.44672 7993.96697) (6331.07115 7997.73100)
(6447.95690 7997.88552) (6455.50554 8001.50837)))
("SF_ARCHITECTURE" 0 ((6236.80215 5535.44536) (6236.80215 5098.03880)))
("SF_ARCHITECTURE" 0 ((6236.80215 5535.44536) (6248.11437 5539.06742) (6285.82229 5539.06742) (6304.67545 5531.67421)))
("SF_ARCHITECTURE" 0 ((6236.80215 5098.03880) (6236.80215 5064.10215)))
("SF_ARCHITECTURE" 0 ((6240.57342 4151.58371) (6236.80837 4166.66708) (6236.80215 5064.10215)))
("SF_PLANTING" 0 ((6315.98767 4068.62704) (6293.36324 4077.22545) (6270.73880 4093.96595) (6236.80215 4095.02262)))
("SF_PLANTING" 0 ((6236.80215 4027.14932) (6236.80215 4095.02262)))
("SF_PLANTING" 0 ((6236.80215 4027.14932) (6236.80215 4008.29604)))
("SF_PLANTING" 0 ((6300.90498 4019.60826) (6293.35701 4030.76550) (6285.82229 4034.53643) (6259.42658 4034.54253)
(6236.80215 4027.14932)))
("SF_PLANTING" 0 ((6253.77048 3949.84876) (6248.33676 3959.20871) (6247.05803 3993.21267) (6236.80215 4008.29604)))
("SF_PLANTING" 0 ((6240.57342 1001.13122) (6240.42568 1036.95419) (6235.13066 1059.57862) (6236.80215 1089.74265)))
("SF_PLANTING" 0 ((6244.34389 1093.51527) (6236.80215 1089.74265)))
("SF_PLANTING" 0 ((6236.80215 361.99095) (6251.88563 348.11233) (6282.04480 341.93292) (6293.51176 329.25916)
(6308.44672 326.85633) (6361.23654 291.53812) (6376.32002 286.72364) (6397.05882 286.57523)))
("SF_PLANTING" 0 ((6240.57342 4151.58371) (6259.42658 4140.27149)))
("SF_PLANTING" 0 ((6244.34389 1136.87783) (6244.19615 1172.70079) (6240.57342 1184.01301)))
("SF_PLANTING" 0 ((6248.11437 1195.32523) (6240.57342 1184.01301)))
("SF_PLANTING" 0 ((6240.57342 1001.13122) (6248.12127 1000.51742) (6270.73880 1010.41007) (6315.98767 1006.78733)))
("SF_SOLAR" 0 ((6244.34389 7967.57172) (6266.96833 7971.33575) (6485.67093 7971.34231)))
("SF_PLANTING" 0 ((6244.34389 1136.87783) (6270.73880 1134.84378) (6285.82229 1127.30351) (6311.01923 1104.67907)
(6315.98767 1082.20305)))
("SF_PLANTING" 0 ((6244.34389 1136.87783) (6240.57342 1116.13971) (6244.34389 1093.51527)))
("SF_PLANTING" 0 ((6244.34389 1093.51527) (6315.98767 1082.20305)))
("SF_PLANTING" 0 ((6244.34389 437.40667) (6236.95679 414.78224) (6245.39333 396.08224) (6251.88563 392.15781)))
("SF_PLANTING" 0 ((6315.98767 279.03563) (6297.13450 300.60294) (6271.57500 307.78914) (6248.26900 290.34785)
(6244.34389 275.26301)))
("SF_PLANTING" 0 ((6244.34389 275.26301) (6266.96833 278.73869) (6278.28054 275.26301)))
("SF_SOLAR" 0 ((6248.11437 8073.15226) (6248.11437 8084.46448)))
("SF_SOLAR" 0 ((6248.11437 8024.13281) (6248.11437 8039.21561)))
("SF_SOLAR" 0 ((6248.11437 7839.36652) (6602.56437 7839.36652)))
("SF_PLANTING" 0 ((6270.73880 3631.22172) (6248.11437 3668.92952)))
("SF_PLANTING" 0 ((6259.42658 3717.94830) (6248.11437 3668.92952)))
("SF_PLANTING" 0 ((6289.59276 3239.06482) (6274.51007 3239.06482) (6248.11437 3239.06482)))
("SF_MASONRY_AND_ARCH" 0 ((6251.88563 2960.03043) (6251.87941 3190.04525) (6248.11437 3239.06482)))
("SF_PLANTING" 0 ((6248.11437 1195.32523) (6274.51007 1191.55260) (6300.90498 1195.32523)))
("SF_MASONRY_AND_ARCH" 0 ((6248.11437 1195.32523) (6248.11459 1217.94966) (6248.11459 1266.96833) (6248.11459
2134.23857) (6248.11459 2149.32127)))
("SF_MASONRY_AND_ARCH" 0 ((6251.88563 2205.88235) (6248.11459 2149.32127)))
("SF_MASONRY_AND_ARCH" 0 ((6251.88563 2960.03043) (6285.82229 2960.03043)))
("SF_MASONRY_AND_ARCH" 0 ((6251.88563 2205.88235) (6274.51007 2204.82602) (6285.82206 2194.57014)))
("SF_PLANTING" 0 ((6304.67545 456.25848) (6289.59276 461.22828) (6271.94299 478.88292) (6269.68247 501.50735)
(6251.88563 535.44400)))
("SF_PLANTING" 0 ((6253.77048 3949.84876) (6263.19785 3932.88043)))
("SF_PLANTING" 0 ((6253.77048 3949.84876) (6274.51007 3965.61980) (6297.13450 3974.35939)))
("SF_PLANTING" 0 ((6259.42658 3717.94830) (6255.65611 3736.80283)))
("SF_PLANTING" 0 ((6289.59276 3782.05170) (6255.65611 3736.80283)))
("SF_PLANTING" 0 ((6255.65611 3337.10407) (6259.42658 3359.72851)))
("SF_PLANTING" 0 ((6259.42658 3883.86165) (6263.19785 3857.46606)))
("SF_PLANTING" 0 ((6259.42658 3883.86165) (6263.19785 3932.88043)))
("SF_PLANTING" 0 ((6259.42658 3717.94830) (6312.21719 3718.09672) (6338.61210 3725.34219) (6368.77828 3725.49061)))
("SF_SOLAR" 0 ((6270.73880 7986.42534) (6263.19785 7978.88394)))
("SF_PLANTING" 0 ((6263.19785 3932.88043) (6312.21719 3932.88043)))
("SF_PLANTING" 0 ((6263.19785 3857.46606) (6285.82229 3831.07048)))
("SF_PLANTING" 0 ((6263.19785 3595.39943) (6346.14695 3578.59276) (6352.49140 3582.35701) (6354.89344 3604.82681)
(6365.00781 3616.13903)))
("SF_PLANTING" 0 ((6300.90498 3540.72398) (6268.17251 3563.35532) (6263.19785 3595.39943)))
("SF_PLANTING" 0 ((6270.73880 3631.22172) (6270.59106 3616.13903) (6263.19785 3595.39943)))
("SF_MASONRY_AND_ARCH" 0 ((6263.19785 2579.18552) (6278.28054 2575.42127) (6304.67545 2579.03088) (6338.61210
2564.10283)))
("SF_SOLAR" 0 ((6266.96833 7937.40577) (6500.75441 7937.40577)))
("SF_PLANTING" 0 ((6327.29989 3612.36776) (6297.13450 3626.39514) (6270.73880 3631.22172)))
("SF_SOLAR" 0 ((6357.46606 8144.79638) (6346.15385 8141.17364) (6282.05102 8141.02557)))
("SF_SOLAR" 0 ((6282.05102 8084.46448) (6282.05102 8069.38167)))
("SF_ARCHITECTURE" 0 ((6662.89593 5607.08857) (6651.58371 5618.40124) (6282.05102 5618.40124)))
("SF_MASONRY_AND_ARCH" 0 ((6285.82206 2194.57014) (6285.82206 2058.82353) (6300.90498 2043.74084)))
("SF_MASONRY_AND_ARCH" 0 ((6285.82206 2194.57014) (6308.43982 2197.13654) (6315.83303 2187.02839) (6315.83303
2062.59400) (6300.90498 2043.74084)))
("SF_PLANTING" 0 ((6285.82229 3831.07048) (6285.82229 3800.90498)))
("SF_PLANTING" 0 ((6285.82229 3831.07048) (6312.21719 3834.84163)))
("SF_PLANTING" 0 ((6289.59276 3782.05170) (6285.82229 3800.90498)))
("SF_MASONRY_AND_ARCH" 0 ((6285.82229 2960.03043) (6323.52941 2960.03043)))
("SF_MASONRY_AND_ARCH" 0 ((6285.82229 2960.03043) (6285.97002 3005.27930) (6289.58654 3020.36199) (6289.58654
3178.73303) (6286.11844 3193.81572) (6289.59276 3239.06482)))
("SF_PLANTING" 0 ((6285.82229 916.28959) (6315.98767 897.59027) (6349.92432 902.41097) (6361.23654 912.51980)))
("SF_PLANTING" 0 ((6285.82229 916.28959) (6301.05962 950.07161) (6315.98767 953.84276) (6361.23654 912.51980)))
("SF_SOLAR" 0 ((6289.59276 8039.21561) (6293.36324 8035.44502) (6293.36324 8024.13281)))
("SF_PLANTING" 0 ((6342.38337 3785.82161) (6289.59276 3782.05170)))
("SF_PLANTING" 0 ((6289.59276 3239.06482) (6323.52941 3239.06482)))
("SF_PLANTING" 0 ((6289.59276 267.72342) (6293.36324 241.32636)))
("SF_PLANTING" 0 ((6293.36324 241.32636) (6372.54876 237.56278) (6395.17319 245.09898)))
("SF_SOLAR" 0 ((6297.13450 7926.09355) (6297.13450 7914.78133)))
("SF_PLANTING" 0 ((6297.13450 3974.35939) (6319.75894 3959.27602)))
("SF_PLANTING" 0 ((6300.90498 4019.60826) (6297.28224 4008.29536) (6297.13450 3974.35939)))
("SF_SOLAR" 0 ((6300.90498 7986.42534) (6300.90498 7978.88394)))
("SF_PLANTING" 0 ((6338.61210 4023.37817) (6300.90498 4019.60826)))
("SF_PLANTING" 0 ((6300.90498 3540.72398) (6319.75894 3540.72398)))
("SF_PLANTING" 0 ((6300.90498 3540.72398) (6305.87964 3506.78733) (6319.59729 3487.93337) (6315.98767 3476.62115)))
("SF_MASONRY_AND_ARCH" 0 ((6300.90498 2021.11640) (6300.90498 2043.74084)))
("SF_MASONRY_AND_ARCH" 0 ((6300.90498 2021.11640) (6308.44672 2017.34514)))
("SF_MASONRY_AND_ARCH" 0 ((6300.90498 2021.11640) (6304.67545 2013.57466) (6308.44672 2017.34514)))
("SF_MASONRY_AND_ARCH" 0 ((6300.90498 2021.11640) (6285.82206 2013.56776) (6285.82206 1972.09627) (6300.90498
1957.01357)))
("SF_MASONRY_AND_ARCH" 0 ((6300.90498 1957.01357) (6300.90498 1195.32523)))
("SF_MASONRY_AND_ARCH" 0 ((6308.44672 2017.34514) (6315.83303 2009.79729) (6315.83303 1975.86753) (6300.90498
1957.01357)))
("SF_PLANTING" 0 ((6323.52941 1172.70079) (6312.36493 1176.62523) (6300.90498 1195.32523)))
("SF_ARCHITECTURE" 0 ((6327.29989 4083.71041) (6304.68167 4151.58371) (6304.66923 5022.62443) (6300.90498 5045.24887)
(6300.91120 5452.48869) (6304.52771 5467.57206) (6304.67545 5531.67421)))
("SF_ARCHITECTURE" 0 ((6376.32002 5531.67421) (6349.92432 5539.21527) (6323.52941 5539.06742) (6304.67545 5531.67421)))
("SF_PLANTING" 0 ((6308.44672 448.71889) (6304.67545 456.25848)))
("SF_PLANTING" 0 ((6319.75894 467.57070) (6304.67545 456.25848)))
("SF_PLANTING" 0 ((6304.67545 358.22115) (6342.38337 358.22115)))
("SF_SOLAR" 0 ((6312.21719 8122.17195) (6315.98767 8129.71335)))
("SF_SOLAR" 0 ((6383.86097 8092.00611) (6365.00781 8088.23529) (6319.76516 8088.38326) (6312.21719 8092.00611)))
("SF_PLANTING" 0 ((6315.98767 3891.40271) (6312.21719 3932.88043)))
("SF_PLANTING" 0 ((6312.21719 3932.88043) (6319.75894 3959.27602)))
("SF_PLANTING" 0 ((6346.15385 3834.84163) (6312.21719 3834.84163)))
("SF_PLANTING" 0 ((6315.98767 3891.40271) (6308.59514 3865.00713) (6312.21719 3834.84163)))
("SF_PLANTING" 0 ((6315.98767 1006.78733) (6312.21719 1025.64197)))
("SF_SOLAR" 0 ((6315.98767 7956.25939) (6315.98767 7948.71799)))
("SF_PLANTING" 0 ((6315.98767 3891.40271) (6338.61210 3891.40271)))
("SF_PLANTING" 0 ((6380.09050 1036.95419) (6361.23654 1041.92195) (6331.07115 1063.50305) (6315.98767 1082.20305)))
("SF_PLANTING" 0 ((6383.86097 961.53846) (6353.69559 970.28428) (6315.98767 1006.78733)))
("SF_PLANTING" 0 ((6315.98767 478.88292) (6319.75894 467.57070)))
("SF_SOLAR" 0 ((6319.75894 8069.38167) (6323.52941 8080.69389)))
("SF_PLANTING" 0 ((6319.75894 3959.27602) (6338.61210 3959.27602)))
("SF_PLANTING" 0 ((6365.00781 441.17647) (6319.75894 467.57070)))
("SF_PLANTING" 0 ((6349.92432 3239.06482) (6323.52941 3239.06482)))
("SF_MASONRY_AND_ARCH" 0 ((6323.52941 2960.03043) (6319.75894 3027.90373) (6323.52319 3058.06912) (6323.52941
3239.06482)))
("SF_MASONRY_AND_ARCH" 0 ((6349.92432 2960.03043) (6323.52941 2960.03043)))
("SF_PLANTING" 0 ((6349.92432 1089.74265) (6348.86799 1104.82749) (6323.52941 1172.70079)))
("SF_PLANTING" 0 ((6323.52941 1172.70079) (6338.61210 1177.66855) (6365.00781 1199.09502)))
("SF_SOLAR" 0 ((6334.84163 7978.88394) (6331.07115 7986.42534)))
("SF_ARCHITECTURE" 0 ((6670.43767 5701.35747) (6659.12545 5705.12172) (6376.32002 5705.27647) (6338.61900 5710.10294)
(6331.07115 5720.21109)))
("SF_ARCHITECTURE" 0 ((6840.12093 5735.29412) (6726.99876 5735.28756) (6704.37432 5731.52330) (6621.41753 5735.29412)
(6602.56437 5735.29412) (6346.15385 5735.29412) (6331.07115 5720.21109)))
("SF_SOLAR" 0 ((6334.84163 8129.71335) (6342.38337 8118.40113)))
("SF_MASONRY_AND_ARCH" 0 ((6334.84163 2435.89717) (6334.84163 2443.43891)))
("SF_PLANTING" 0 ((6334.84163 392.15781) (6342.38337 388.38518)))
("SF_SOLAR" 0 ((6338.61210 7922.32274) (6338.61210 7929.86425)))
("SF_PLANTING" 0 ((6338.61210 4023.37817) (6338.61210 4019.60826) (6349.92432 4012.06595)))
("SF_PLANTING" 0 ((6338.61210 4023.37817) (6346.30848 4042.07771) (6353.69559 4045.84864) (6365.00090 4044.79876)
(6375.26357 4030.92048) (6376.32002 4012.06595)))
("SF_PLANTING" 0 ((6361.23654 3951.73495) (6338.61210 3959.27602)))
("SF_PLANTING" 0 ((6349.92432 4012.06595) (6338.75984 3974.35939) (6338.61210 3959.27602)))
("SF_PLANTING" 0 ((6346.15385 3834.84163) (6346.00611 3861.23722) (6338.61210 3891.40271)))
("SF_PLANTING" 0 ((6436.65158 3940.42274) (6395.17319 3931.68314) (6357.46606 3909.20645) (6338.61210 3891.40271)))
("SF_MASONRY_AND_ARCH" 0 ((6644.04197 2567.87330) (6613.87658 2564.10905) (6489.44219 2563.95509) (6474.35871
2560.33778) (6338.61210 2564.10283)))
("SF_MASONRY_AND_ARCH" 0 ((6855.20362 2496.22952) (6832.57919 2499.99310) (6813.72523 2496.38416) (6791.10079
2499.85158) (6776.01810 2496.24265) (6757.16414 2499.99378) (6659.12545 2499.84536) (6651.73835 2496.07489) (6646.60905
2481.15294) (6636.50102 2473.75973) (6553.54423 2473.59887) (6530.91980 2469.83382) (6346.16075 2473.75973) (6339.81629
2477.53020) (6337.56267 2496.22952) (6327.45452 2522.62443) (6338.61210 2564.10283)))
("SF_SOLAR" 0 ((6342.38337 8042.98643) (6383.86097 8039.21561)))
("SF_PLANTING" 0 ((6342.38337 3785.82161) (6368.77828 3736.80283)))
("SF_PLANTING" 0 ((6342.38337 3785.82161) (6343.43281 3800.90498) (6353.69559 3831.07048)))
("SF_PLANTING" 0 ((6342.38337 358.22115) (6342.38337 388.38518)))
("SF_PLANTING" 0 ((6365.00781 403.47002) (6342.38337 388.38518)))
("SF_PLANTING" 0 ((6398.94446 320.51188) (6372.54876 333.02274) (6342.38337 358.22115)))
("SF_SOLAR" 0 ((6346.15385 7960.03020) (6349.92432 7952.48869)))
("SF_PLANTING" 0 ((6346.15385 3834.84163) (6353.69559 3831.07048)))
("SF_PLANTING" 0 ((6349.92432 3676.47059) (6346.15385 3687.78281)))
("SF_SOLAR" 0 ((6349.92432 8156.10860) (6357.46606 8144.79638)))
("SF_SOLAR" 0 ((6349.92432 8035.44502) (6358.52240 8016.74593) (6365.01403 8012.97523) (6429.10984 8013.11652)
(6444.19333 8016.59118)))
("SF_PLANTING" 0 ((6349.92432 4012.06595) (6376.32002 4012.06595)))
("SF_PLANTING" 0 ((6349.92432 3239.06482) (6357.47296 3239.06482) (6391.40271 3239.06482) (6410.25667 3227.75238)))
("SF_MASONRY_AND_ARCH" 0 ((6349.92432 2960.03043) (6353.69559 2982.65486) (6349.93054 3024.13247) (6353.69559
3088.23529) (6349.93054 3110.85973) (6349.92432 3239.06482)))
("SF_MASONRY_AND_ARCH" 0 ((6410.25667 2967.57138) (6383.86097 2956.40690) (6349.92432 2960.03043)))
("SF_PLANTING" 0 ((6353.69559 3831.07048) (6368.77828 3834.84163)))
("SF_SOLAR" 0 ((6406.48541 8095.77670) (6376.32002 8129.71335) (6357.46606 8144.79638)))
("SF_SOLAR" 0 ((6361.23654 7982.65452) (6361.23654 7990.19615)))
("SF_PLANTING" 0 ((6361.23654 4083.71041) (6366.06414 4110.10532) (6376.32002 4121.41821)))
("SF_PLANTING" 0 ((6361.23654 3631.22172) (6365.00781 3616.13903)))
("SF_PLANTING" 0 ((6380.09050 912.51980) (6361.23654 912.51980)))
("SF_PLANTING" 0 ((6402.71493 3616.13903) (6365.00781 3616.13903)))
("SF_MASONRY_AND_ARCH" 0 ((6365.00781 1500.75509) (6365.00781 1199.09502)))
("SF_PLANTING" 0 ((6365.00781 1199.09502) (6383.86120 1187.78281) (6383.86120 1168.92817)))
("SF_PLANTING" 0 ((6365.00781 441.17647) (6383.86097 441.17647)))
("SF_PLANTING" 0 ((6365.00781 441.17647) (6365.00781 403.47002)))
("SF_PLANTING" 0 ((6417.79762 346.90894) (6387.48371 384.61538) (6365.00781 403.47002)))
("SF_PLANTING" 0 ((6380.09050 3891.40271) (6368.77828 3891.40271)))
("SF_PLANTING" 0 ((6368.77828 3834.84163) (6376.32624 3827.60305) (6466.81776 3834.99627) (6481.90045 3842.38269)))
("SF_PLANTING" 0 ((6414.02715 3883.86165) (6388.68167 3861.08880) (6368.77828 3834.84163)))
("SF_PLANTING" 0 ((6368.77828 3736.80283) (6398.94446 3735.74615) (6429.10984 3721.71946)))
("SF_PLANTING" 0 ((6368.77828 3736.80283) (6368.77828 3725.49061)))
("SF_PLANTING" 0 ((6383.86097 3702.86618) (6368.77828 3725.49061)))
("SF_SOLAR" 0 ((6383.86097 8148.56719) (6376.32002 8144.79638)))
("SF_ARCHITECTURE" 0 ((6376.32002 5531.67421) (6376.32624 5399.69876) (6380.09050 5377.07432) (6376.32624 4272.24695)
(6380.09050 4253.39367)))
("SF_ARCHITECTURE" 0 ((6376.32002 5531.67421) (6406.48541 5539.21527) (6432.88111 5539.06742) (6447.96380 5531.67421)))
("SF_PLANTING" 0 ((6414.02715 4053.54491) (6403.77127 4064.85713) (6402.56719 4087.48156) (6394.11686 4110.09910)
(6376.32002 4121.41821)))
("SF_PLANTING" 0 ((6380.09050 4253.39367) (6362.44072 4238.31029) (6357.76222 4219.45701) (6376.32002 4121.41821)))
("SF_PLANTING" 0 ((6429.10984 3974.35939) (6402.71493 3979.33405) (6387.78688 3993.21267) (6376.32002 4012.06595)))
("SF_PLANTING" 0 ((6376.32002 1142.53394) (6383.86120 1168.92817)))
("SF_PLANTING" 0 ((6380.09050 4253.39367) (6390.34638 4242.08145) (6396.37115 4223.22817) (6410.40441 4200.60995)
(6436.65158 4186.57704) (6447.96380 4185.52036)))
("SF_PLANTING" 0 ((6391.40271 3657.61731) (6380.09050 3650.07500)))
("SF_PLANTING" 0 ((6398.94446 1070.89084) (6385.05894 1085.97285) (6380.09050 1101.05486)))
("SF_PLANTING" 0 ((6391.40271 972.85068) (6384.00871 999.24491) (6380.09050 1036.95419)))
("SF_PLANTING" 0 ((6380.09050 1036.95419) (6387.63846 1043.29661) (6398.94446 1044.49378)))
("SF_PLANTING" 0 ((6380.09050 912.51980) (6391.40271 902.41097) (6410.25667 897.58337) (6432.88111 897.58337)
(6451.73428 904.97738)))
("SF_PLANTING" 0 ((6380.09050 912.51980) (6383.86097 961.53846)))
("SF_SOLAR" 0 ((6383.86097 8039.21561) (6383.86097 8020.36199)))
("SF_SOLAR" 0 ((6383.86097 8039.21561) (6425.33937 8042.98643)))
("SF_SOLAR" 0 ((6383.86097 7960.03020) (6383.86097 7952.48869)))
("SF_PLANTING" 0 ((6383.86097 3702.86618) (6391.40271 3657.61731)))
("SF_PLANTING" 0 ((6383.86097 3702.86618) (6402.71493 3706.63609)))
("SF_MASONRY_AND_ARCH" 0 ((6500.75441 2386.87783) (6383.86097 2386.87783)))
("SF_PLANTING" 0 ((6391.40271 972.85068) (6383.86097 961.53846)))
("SF_PLANTING" 0 ((6383.86097 441.17647) (6427.91199 380.84559) (6432.88111 365.76075)))
("SF_PLANTING" 0 ((6395.17319 482.65554) (6397.74027 467.57070) (6383.86097 441.17647)))
("SF_PLANTING" 0 ((6414.02715 1168.92817) (6383.86120 1168.92817)))
("SF_SOLAR" 0 ((6391.40271 8159.87941) (6398.95068 8148.56719) (6414.02715 8137.25498)))
("SF_SOLAR" 0 ((6391.40271 8159.87941) (6402.71493 8163.64344) (6625.18880 8163.65000)))
("SF_PLANTING" 0 ((6430.99548 3633.10667) (6414.02715 3649.01957) (6391.40271 3657.61731)))
("SF_PLANTING" 0 ((6391.40271 972.85068) (6432.88111 972.70226) (6447.96380 965.30826)))
("SF_PLANTING" 0 ((6414.02715 3883.86165) (6406.33145 3897.74649) (6395.17319 3902.71493)))
("SF_PLANTING" 0 ((6395.17319 245.09898) (6414.02715 237.70430) (6444.19333 237.71120) (6470.58824 260.18100)))
("SF_PLANTING" 0 ((6395.17319 245.09898) (6397.05882 286.57523)))
("SF_PLANTING" 0 ((6397.05882 286.57523) (6410.25317 279.18891) (6447.96380 279.03563)))
("SF_PLANTING" 0 ((6398.94446 320.51188) (6397.05882 286.57523)))
("SF_PLANTING" 0 ((6398.94446 1070.89084) (6398.94446 1044.49378)))
("SF_PLANTING" 0 ((6417.79762 1089.74265) (6398.94446 1070.89084)))
("SF_PLANTING" 0 ((6461.16165 1042.61029) (6417.79762 1040.73020) (6398.94446 1044.49378)))
("SF_PLANTING" 0 ((6398.94446 320.51188) (6417.79762 324.28450)))
("SF_SOLAR" 0 ((6402.71493 7986.42534) (6402.71493 7978.88394)))
("SF_PLANTING" 0 ((6414.02715 3559.57794) (6399.09287 3582.20238) (6402.71493 3616.13903)))
("SF_PLANTING" 0 ((6402.71493 3616.13903) (6417.79140 3617.34310) (6430.99548 3633.10667)))
("SF_MASONRY_AND_ARCH" 0 ((6527.14932 2662.14152) (6481.90045 2665.91278) (6432.88111 2665.76505) (6417.79762
2662.29615) (6402.71493 2665.91278)))
("SF_SOLAR" 0 ((6406.48541 8095.77670) (6421.56889 8061.84005)))
("SF_SOLAR" 0 ((6406.48541 8095.77670) (6414.02715 8103.31833)))
("SF_PLANTING" 0 ((6414.02715 3518.09955) (6407.67647 3522.02466) (6406.48541 3536.95351)))
("SF_MASONRY_AND_ARCH" 0 ((6410.25667 2967.57138) (6410.25667 3227.75238)))
("SF_PLANTING" 0 ((6481.90045 3227.75238) (6466.81776 3239.06482) (6429.10984 3239.06482) (6410.25667 3227.75238)))
("SF_MASONRY_AND_ARCH" 0 ((6410.25667 2967.57138) (6444.19333 2956.25916) (6478.12998 2967.57138)))
("SF_SOLAR" 0 ((6568.62771 7937.40577) (6557.31550 7941.33111) (6523.52658 7975.11312) (6414.02715 8137.25498)))
("SF_SOLAR" 0 ((6414.02715 8137.25498) (6432.88111 8143.59876) (6617.64706 8141.03213) (6628.95928 8144.79638)))
("SF_SOLAR" 0 ((6417.79762 8024.13281) (6414.02715 8031.67421)))
("SF_PLANTING" 0 ((6429.10984 3974.35939) (6414.02715 4053.54491)))
("SF_PLANTING" 0 ((6447.96380 4185.52036) (6443.13688 4072.39819) (6436.50317 4062.14265) (6414.02715 4053.54491)))
("SF_PLANTING" 0 ((6414.02715 3883.86165) (6444.19333 3884.91776) (6474.35871 3906.48609)))
("SF_MASONRY_AND_ARCH" 0 ((6414.02715 2205.88235) (6417.79785 2198.34061)))
("SF_PLANTING" 0 ((6414.02715 1168.92817) (6421.56889 1138.76414)))
("SF_PLANTING" 0 ((6414.02715 1168.92817) (6417.79785 1184.01301)))
("SF_SOLAR" 0 ((6417.79762 7948.71799) (6417.79762 7960.03020)))
("SF_PLANTING" 0 ((6417.79762 3778.28054) (6432.88111 3785.82161)))
("SF_PLANTING" 0 ((6444.19333 1089.74265) (6417.79762 1089.74265)))
("SF_PLANTING" 0 ((6417.79762 1089.74265) (6421.56889 1138.76414)))
("SF_PLANTING" 0 ((6432.88111 509.04977) (6418.85407 535.44400) (6417.79762 565.61086)))
("SF_PLANTING" 0 ((6628.95928 595.77771) (6620.36120 573.30034) (6606.33484 565.75928) (6579.93993 569.37443)
(6553.54423 565.61086) (6530.91980 569.37579) (6432.88111 569.38066) (6417.79762 565.61086)))
("SF_PLANTING" 0 ((6417.79762 346.90894) (6417.79762 324.28450)))
("SF_PLANTING" 0 ((6417.79762 346.90894) (6432.88111 365.76075)))
("SF_PLANTING" 0 ((6447.96380 279.03563) (6447.80916 297.88744) (6432.87421 319.45622) (6417.79762 324.28450)))
("SF_MASONRY_AND_ARCH" 0 ((6451.73428 2190.79966) (6440.42206 2198.18597) (6417.79785 2198.34061)))
("SF_MASONRY_AND_ARCH" 0 ((6417.79785 2198.34061) (6417.79785 2187.02839) (6417.79785 1319.75962) (6417.79785
1300.90498) (6417.79785 1270.73812) (6417.79785 1202.86482) (6417.79785 1184.01301)))
("SF_PLANTING" 0 ((6444.19333 1184.01301) (6417.79785 1184.01301)))
("SF_SOLAR" 0 ((6421.56889 8061.84005) (6428.96833 8057.91471) (6484.47308 7978.89050) (6485.67093 7971.34231)))
("SF_PLANTING" 0 ((6421.56889 3472.85068) (6429.10984 3487.93337)))
("SF_PLANTING" 0 ((6444.19333 1138.76414) (6421.56889 1138.76414)))
("SF_SOLAR" 0 ((6429.10984 7918.55204) (6429.10984 7929.86425)))
("SF_PLANTING" 0 ((6429.10984 3974.35939) (6436.50385 3955.50486) (6436.65158 3940.42274)))
("SF_PLANTING" 0 ((6493.21267 3676.47059) (6451.73428 3677.67511) (6430.31403 3699.09502) (6429.10984 3721.71946)))
("SF_PLANTING" 0 ((6429.10984 3721.71946) (6443.82455 3726.68133) (6444.19333 3733.03167)))
("SF_MASONRY_AND_ARCH" 0 ((6429.10984 2307.69231) (6493.21267 2307.54389) (6512.06663 2300.15057)))
("SF_PLANTING" 0 ((6466.81776 361.99095) (6465.76753 384.61538) (6452.78450 414.78224) (6446.92059 441.17647)
(6429.10984 475.11312)))
("SF_PLANTING" 0 ((6430.99548 3633.10667) (6470.58824 3623.68066)))
("SF_PLANTING" 0 ((6444.19333 3657.61731) (6430.99548 3633.10667)))
("SF_PLANTING" 0 ((6466.81776 361.99095) (6432.88111 365.76075)))
("SF_PLANTING" 0 ((6474.35871 3917.79830) (6463.04649 3928.05385) (6436.65158 3940.42274)))
("SF_PLANTING" 0 ((6440.42206 3503.01686) (6436.65158 3510.55781)))
("SF_SOLAR" 0 ((6440.42206 8058.06946) (6451.73428 8061.84005)))
("SF_SOLAR" 0 ((6444.19333 7982.65452) (6440.42206 7990.19615)))
("SF_MASONRY_AND_ARCH" 0 ((6651.58371 2639.51708) (6628.95928 2633.17398) (6527.14932 2635.74038) (6478.12998
2631.98235) (6459.27602 2635.59197) (6444.19333 2631.97613)))
("SF_PLANTING" 0 ((6459.27602 1187.78281) (6455.50554 1184.01301) (6444.19333 1184.01301)))
("SF_PLANTING" 0 ((6444.19333 1184.01301) (6447.96380 1146.30373)))
("SF_MASONRY_AND_ARCH" 0 ((6444.19333 1184.01301) (6444.34106 1229.26188) (6447.96380 1244.34389) (6447.96380
1504.52489) (6447.96380 1527.14932) (6447.97002 2138.00905) (6451.73428 2190.79966)))
("SF_PLANTING" 0 ((6444.19333 1138.76414) (6451.73428 1104.82749)))
("SF_PLANTING" 0 ((6444.19333 1138.76414) (6447.96380 1146.30373)))
("SF_PLANTING" 0 ((6461.16165 1042.61029) (6445.24966 1063.34842) (6444.19333 1089.74265)))
("SF_PLANTING" 0 ((6444.19333 1089.74265) (6451.73428 1104.82749)))
("SF_SOLAR" 0 ((6644.04197 8103.31833) (6561.08597 8095.93133) (6549.77376 8099.39955) (6466.81776 8099.69548)
(6447.96380 8107.08891)))
("SF_ARCHITECTURE" 0 ((6447.96380 4185.52036) (6451.73428 4200.60373) (6447.97002 4245.85260) (6447.97002 4370.28699)
(6451.72805 4389.14027) (6447.96380 4626.69683) (6451.72805 4649.32127) (6451.72805 4781.29672) (6447.97692 4800.15124)
(6451.72805 4819.00452) (6451.73428 5139.51776) (6447.97002 5162.14219) (6447.96380 5531.67421)))
("SF_ARCHITECTURE" 0 ((6519.60758 5531.67421) (6496.98314 5539.21527) (6466.81776 5539.06742) (6447.96380 5531.67421)))
("SF_PLANTING" 0 ((6455.50554 1150.07636) (6447.96380 1146.30373)))
("SF_PLANTING" 0 ((6447.96380 965.30826) (6451.73428 942.68382)))
("SF_PLANTING" 0 ((6455.50554 972.85068) (6447.96380 965.30826)))
("SF_PLANTING" 0 ((6470.58824 260.18100) (6459.27602 275.10973) (6447.96380 279.03563)))
("SF_MASONRY_AND_ARCH" 0 ((6496.98337 1172.70079) (6489.44842 1248.11369) (6496.98337 1266.96833) (6496.98337
1432.88179) (6496.98337 1512.06731) (6496.98337 1644.04129) (6496.98337 1666.66572) (6496.98337 2115.38462) (6496.98337
2156.86301) (6496.98337 2179.48054) (6485.66471 2185.97206) (6474.35871 2190.65113) (6451.73428 2190.79966)))
("SF_PLANTING" 0 ((6451.73428 1104.82749) (6481.90045 1104.82749)))
("SF_PLANTING" 0 ((6493.21267 931.37161) (6451.73428 942.68382)))
("SF_PLANTING" 0 ((6451.73428 904.97738) (6451.73428 942.68382)))
("SF_PLANTING" 0 ((6496.98314 916.28959) (6481.90045 905.13201) (6451.73428 904.97738)))
("SF_SOLAR" 0 ((6455.50554 7952.48869) (6459.27602 7960.03020)))
("SF_PLANTING" 0 ((6455.50554 972.85068) (6496.98314 972.85068)))
("SF_PLANTING" 0 ((6455.50554 972.85068) (6455.65328 999.24491) (6463.04649 1029.41176)))
("SF_PLANTING" 0 ((6461.16165 1042.61029) (6463.04649 1029.41176)))
("SF_PLANTING" 0 ((6461.16165 1042.61029) (6481.90045 1085.97285)))
("SF_PLANTING" 0 ((6461.16165 1042.61029) (6500.75441 1048.26640)))
("SF_PLANTING" 0 ((6493.21267 3676.47059) (6496.83541 3687.78281) (6495.77907 3710.40102) (6485.67093 3717.79434)
(6463.04649 3717.94830)))
("SF_PLANTING" 0 ((6496.98314 1014.32975) (6481.90045 1015.53314) (6463.04649 1029.41176)))
("SF_PLANTING" 0 ((6466.81776 3789.59276) (6474.35871 3782.05170)))
("SF_PLANTING" 0 ((6466.81776 3755.65611) (6474.35871 3763.19717) (6474.35871 3770.73948)))
("SF_PLANTING" 0 ((6466.81776 361.99095) (6475.41516 316.74208) (6489.44219 297.88744)))
("SF_PLANTING" 0 ((6470.58824 3616.13903) (6470.58824 3623.68066)))
("SF_PLANTING" 0 ((6493.21267 3634.99287) (6470.58824 3623.68066)))
("SF_PLANTING" 0 ((6519.60758 384.61538) (6509.49333 395.92760) (6492.00848 463.80090) (6478.13620 478.58122)
(6470.58824 478.88292)))
("SF_PLANTING" 0 ((6470.58824 260.18100) (6485.67093 260.18100)))
("SF_PLANTING" 0 ((6474.35871 3917.79830) (6474.35871 3906.48609)))
("SF_PLANTING" 0 ((6474.35871 3917.79830) (6489.28756 3929.11052) (6496.98314 3944.19265)))
("SF_PLANTING" 0 ((6481.90045 3842.38269) (6481.74581 3895.17319) (6474.35871 3906.48609)))
("SF_SOLAR" 0 ((6478.12998 8061.84005) (6666.66640 8060.16878) (6685.52036 8065.61086)))
("SF_SOLAR" 0 ((6481.90045 8016.59118) (6478.12998 8009.04977)))
("SF_MASONRY_AND_ARCH" 0 ((6542.23201 2960.03043) (6493.21267 2960.18507) (6478.12998 2967.57138)))
("SF_MASONRY_AND_ARCH" 0 ((6481.90045 3227.75238) (6481.89423 3031.67421) (6478.27771 3016.59152) (6478.12998
2967.57138)))
("SF_PLANTING" 0 ((6478.12998 1168.92817) (6496.98337 1172.70079)))
("SF_PLANTING" 0 ((6553.54423 3812.21719) (6527.14932 3812.36527) (6497.13167 3824.58609) (6481.90045 3842.38269)))
("SF_PLANTING" 0 ((6542.23201 3239.06482) (6534.68416 3239.06482) (6500.75441 3239.06482) (6481.90045 3227.75238)))
("SF_PLANTING" 0 ((6481.90045 1104.82749) (6481.90045 1085.97285)))
("SF_PLANTING" 0 ((6496.98337 1150.07636) (6496.98337 1134.99152) (6483.10464 1116.13971) (6481.90045 1104.82749)))
("SF_PLANTING" 0 ((6508.29536 1059.57862) (6504.37025 1078.27715) (6481.90045 1085.97285)))
("SF_SOLAR" 0 ((6485.67093 7993.96674) (6496.98314 7997.73756)))
("SF_SOLAR" 0 ((6530.91980 7918.55204) (6485.67093 7971.34231)))
("SF_SOLAR" 0 ((6485.67093 7926.09355) (6496.98314 7914.78133)))
("SF_PLANTING" 0 ((6508.29536 256.41120) (6485.67093 260.18100)))
("SF_PLANTING" 0 ((6489.44219 297.88744) (6485.67093 260.18100)))
("SF_SOLAR" 0 ((6489.44219 8084.46448) (6489.44219 8073.15226) (6493.21267 8069.38167)))
("SF_PLANTING" 0 ((6489.44219 4008.29604) (6489.59683 3955.50554) (6496.98314 3944.19265)))
("SF_PLANTING" 0 ((6506.03348 4090.49785) (6489.59683 4076.16244) (6489.44219 4008.29604)))
("SF_PLANTING" 0 ((6504.52489 4012.06595) (6489.44219 4008.29604)))
("SF_PLANTING" 0 ((6489.44219 297.88744) (6500.60588 305.43676) (6512.06663 324.28450)))
("SF_PLANTING" 0 ((6493.21267 4234.54038) (6508.29559 4294.87138) (6519.60758 4306.18360)))
("SF_PLANTING" 0 ((6493.21267 3676.47059) (6504.52489 3661.38722)))
("SF_PLANTING" 0 ((6504.52489 3661.38722) (6530.91357 3661.23326) (6537.25735 3657.46233) (6538.31312 3646.30509)
(6533.49310 3631.37636) (6515.83710 3627.59898) (6493.21267 3634.99287)))
("SF_PLANTING" 0 ((6504.52489 3661.38722) (6493.21267 3634.99287)))
("SF_PLANTING" 0 ((6496.98314 916.28959) (6493.21267 931.37161)))
("SF_PLANTING" 0 ((6493.21267 931.37161) (6496.98314 972.85068)))
("SF_SOLAR" 0 ((6696.83258 8042.98643) (6644.04197 8039.21572) (6527.14932 8039.22217) (6508.29536 8042.83190)
(6496.98314 8039.21561)))
("SF_PLANTING" 0 ((6519.60758 3947.96380) (6496.98314 3944.19265)))
("SF_PLANTING" 0 ((6496.98314 1014.32975) (6496.98314 972.85068)))
("SF_PLANTING" 0 ((6496.98314 1014.32975) (6515.83710 1025.64197)))
("SF_PLANTING" 0 ((6496.98314 916.28959) (6512.06663 916.28959)))
("SF_PLANTING" 0 ((6496.98337 1150.07636) (6496.98337 1172.70079)))
("SF_PLANTING" 0 ((6496.98337 1150.07636) (6546.00328 1157.61595)))
("SF_SOLAR" 0 ((6500.75441 7869.53247) (6527.14932 7869.53247)))
("SF_PLANTING" 0 ((6506.03348 4090.49785) (6497.28835 4102.56290) (6504.22873 4155.35419) (6500.75441 4166.66708)))
("SF_PLANTING" 0 ((6515.83710 1025.64197) (6500.75441 1048.26640)))
("SF_PLANTING" 0 ((6508.29536 1059.57862) (6500.75441 1048.26640)))
("SF_SOLAR" 0 ((6504.52489 8084.46448) (6504.52489 8076.92308)))
("SF_PLANTING" 0 ((6506.03348 4090.49785) (6512.06663 4083.71041) (6523.37885 4083.71041)))
("SF_PLANTING" 1 ((6506.03348 4090.49785) (6508.29536 4098.79378) (6512.06663 4095.02262)))
("SF_PLANTING" 0 ((6538.46154 1052.03620) (6508.29536 1059.57862)))
("SF_PLANTING" 0 ((6508.29536 256.41120) (6523.37885 242.38348) (6534.69106 237.70498) (6587.48088 241.17930)
(6621.41753 233.79921) (6636.50102 238.61290) (6651.58371 252.63857)))
("SF_PLANTING" 0 ((6508.29536 256.41120) (6549.77376 289.14921) (6579.93993 294.11143) (6640.27149 266.66629)
(6651.58371 252.63857)))
("SF_SOLAR" 0 ((6719.45701 8012.82059) (6719.08835 8006.47670) (6538.46154 8005.28552) (6512.06663 8009.04977)))
("SF_PLANTING" 0 ((6583.71041 904.97738) (6572.39819 901.35464) (6534.69106 901.35532) (6512.06663 916.28959)))
("SF_PLANTING" 0 ((6534.69106 938.91403) (6523.37885 931.36674) (6512.06663 916.28959)))
("SF_PLANTING" 0 ((6553.54423 343.13631) (6538.46154 325.48790) (6519.61448 321.71052) (6512.06663 324.28450)))
("SF_PLANTING" 0 ((6519.60758 358.22115) (6515.98484 354.29525) (6512.06663 324.28450)))
("SF_PLANTING" 0 ((6538.46154 1023.75566) (6515.83710 1025.64197)))
("SF_PLANTING" 0 ((6515.83710 482.65554) (6527.14932 467.57070)))
("SF_SOLAR" 0 ((6519.60758 8122.17195) (6527.14932 8129.71335)))
("SF_ARCHITECTURE" 0 ((6519.60758 4306.18360) (6519.60758 5531.67421)))
("SF_ARCHITECTURE" 0 ((6595.02262 5527.90305) (6564.85645 5539.06742) (6538.46154 5539.06742) (6519.60758 5531.67421)))
("SF_PLANTING" 0 ((6519.60758 4306.18360) (6537.25735 4291.10147) (6541.03416 4272.24695) (6533.01946 4200.60373)
(6534.54333 4159.12477) (6527.29706 4128.95928) (6523.37885 4083.71041)))
("SF_PLANTING" 0 ((6519.60758 3947.96380) (6527.15622 3936.65781) (6546.00328 3921.56821)))
("SF_PLANTING" 0 ((6546.00328 3985.67161) (6541.03416 3970.73631) (6519.60758 3947.96380)))
("SF_PLANTING" 0 ((6519.60758 384.61538) (6519.60758 358.22115)))
("SF_PLANTING" 0 ((6519.60758 384.61538) (6542.23201 403.47002)))
("SF_PLANTING" 0 ((6553.54423 343.13631) (6545.99638 349.48077) (6527.15622 351.87670) (6519.60758 358.22115)))
("SF_SOLAR" 0 ((6523.37885 8031.67421) (6523.37885 8020.36199)))
("SF_PLANTING" 0 ((6527.14932 4049.77376) (6529.57421 4076.16244) (6523.37885 4083.71041)))
("SF_SOLAR" 0 ((6527.14932 7941.17647) (6538.46154 7944.94717)))
("SF_MASONRY_AND_ARCH" 0 ((6527.14932 2300.15057) (6549.77376 2305.11968) (6568.62771 2315.08552) (6602.56437
2311.46278)))
("SF_MASONRY_AND_ARCH" 0 ((6534.69106 2383.10735) (6644.04197 2390.64140) (6666.66640 2386.88405) (6764.69898
2387.03247) (6771.04344 2390.80294) (6776.01810 2417.04400)))
("SF_MASONRY_AND_ARCH" 0 ((6602.56437 2273.75566) (6564.85645 2270.13982) (6549.77376 2273.45950) (6534.69106
2269.98518)))
("SF_PLANTING" 0 ((6534.69106 938.91403) (6572.39819 938.91403)))
("SF_PLANTING" 0 ((6534.69106 938.91403) (6534.84570 965.30826) (6542.23201 976.62048)))
("SF_PLANTING" 0 ((6538.46154 1052.03620) (6538.46154 1023.75566)))
("SF_PLANTING" 0 ((6538.46154 1052.03620) (6546.00328 1055.80600)))
("SF_PLANTING" 0 ((6606.33484 1003.01753) (6587.48088 1004.06629) (6538.46154 1023.75566)))
("SF_PLANTING" 0 ((6542.23201 976.62048) (6538.60928 987.93269) (6538.46154 1023.75566)))
("SF_PLANTING" 0 ((6542.23201 3239.06482) (6564.85645 3239.06482)))
("SF_PLANTING" 0 ((6542.23201 3239.06482) (6538.61618 3197.58699) (6549.77376 3182.50351)))
("SF_MASONRY_AND_ARCH" 0 ((6542.23201 2960.03043) (6538.60928 2971.34265) (6538.60928 3005.27930) (6549.77376
3027.90373)))
("SF_MASONRY_AND_ARCH" 0 ((6542.23201 2960.03043) (6602.56437 2960.17817) (6613.87658 2963.80090)))
("SF_PLANTING" 0 ((6542.23201 976.62048) (6572.23665 968.92557) (6574.96459 961.53846) (6572.39819 938.91403)))
("SF_PLANTING" 0 ((6542.23201 403.47002) (6547.05962 426.09446) (6571.20023 467.57070) (6574.97081 486.42534)
(6572.39819 501.50735)))
("SF_PLANTING" 0 ((6542.23201 403.47002) (6564.85023 403.61708) (6572.39819 407.23982)))
("SF_SOLAR" 0 ((6546.00328 7967.57172) (6557.31550 7971.33575) (6745.85192 7971.34231)))
("SF_PLANTING" 0 ((6587.48088 6723.22749) (6557.46324 6738.31753) (6550.83009 6749.62319) (6546.00328 6776.01810)))
("SF_PLANTING" 0 ((6636.50102 6832.57919) (6617.64706 6828.96312) (6598.79310 6832.57262) (6508.30226 6831.37489)
(6500.90905 6821.26697) (6501.95848 6787.33688) (6512.06663 6779.94344) (6546.00328 6776.01810)))
("SF_PLANTING" 0 ((6610.10532 6779.78857) (6583.71041 6783.41154) (6546.00328 6776.01810)))
("SF_PLANTING" 0 ((6546.00328 3985.67161) (6542.38665 3996.98382) (6547.20113 4015.83710) (6576.16867 4049.77376)))
("SF_PLANTING" 0 ((6546.00328 3985.67161) (6564.85645 3993.36731) (6591.25215 4023.37817)))
("SF_PLANTING" 0 ((6564.85645 3865.00713) (6539.67262 3891.40271) (6546.00328 3921.56821)))
("SF_PLANTING" 0 ((6659.12545 3996.98382) (6628.95928 3995.77907) (6614.03122 3981.90045) (6602.41584 3959.42410)
(6561.08597 3926.53699) (6546.00328 3921.56821)))
("SF_PLANTING" 0 ((6546.00328 1157.61595) (6549.77376 1131.22172)))
("SF_PLANTING" 0 ((6677.97862 1134.99152) (6664.09389 1138.38846) (6655.20645 1120.05792) (6617.64706 1097.13665)
(6583.71041 1060.63428) (6561.08597 1053.23416) (6546.00328 1055.80600)))
("SF_PLANTING" 0 ((6549.77376 1093.51527) (6546.00328 1055.80600)))
("SF_MASONRY_AND_ARCH" 0 ((6549.77376 3182.50351) (6553.54423 3156.10860) (6549.77998 3125.94242) (6549.77376
3027.90373)))
("SF_PLANTING" 0 ((6549.77376 3182.50351) (6563.65238 3197.58699) (6564.85645 3239.06482)))
("SF_MASONRY_AND_ARCH" 0 ((6549.77376 3027.90373) (6567.57127 3012.82025) (6572.39819 2993.96708)))
("SF_MASONRY_AND_ARCH" 0 ((6549.77376 2337.85848) (6549.77376 2349.17070)))
("SF_PLANTING" 0 ((6549.77376 1093.51527) (6549.77376 1131.22172)))
("SF_PLANTING" 0 ((6595.02262 1161.38857) (6580.08767 1153.69774) (6568.47919 1136.19016) (6549.77376 1131.22172)))
("SF_PLANTING" 0 ((6549.77376 1093.51527) (6568.62771 1093.66855) (6579.93993 1101.05486)))
("SF_SOLAR" 0 ((6553.54423 8069.38167) (6553.54423 8080.69389)))
("SF_SOLAR" 0 ((6553.54423 7982.65452) (6553.54423 7990.19615)))
("SF_PLANTING" 0 ((6553.54423 3812.21719) (6561.09287 3802.10916) (6591.25215 3800.90498)))
("SF_PLANTING" 0 ((6564.85645 3865.00713) (6553.69197 3831.07048) (6553.54423 3812.21719)))
("SF_PLANTING" 0 ((6738.31097 3729.26052) (6568.62771 3729.25430) (6553.54423 3725.49061)))
("SF_PLANTING" 0 ((6553.54423 343.13631) (6561.08597 343.13631)))
("SF_PLANTING" 0 ((6602.56437 343.13631) (6568.63394 336.80011) (6561.08597 343.13631)))
("SF_PLANTING" 0 ((6561.08597 343.13631) (6576.17557 368.32851) (6594.87421 371.04955) (6602.56437 361.99095)))
("SF_PLANTING" 0 ((6576.16867 3868.77828) (6564.85645 3865.00713)))
("SF_PLANTING" 0 ((6564.85645 3239.06482) (6572.40509 3239.06482) (6602.55747 3239.06482) (6610.10532 3231.52364)))
("SF_SOLAR" 0 ((6568.62771 7937.40577) (6772.24762 7937.40577)))
("SF_SOLAR" 0 ((6568.62771 7937.40577) (6576.16867 7914.78133)))
("SF_SOLAR" 0 ((6572.39819 8129.71335) (6576.16867 8114.63054)))
("SF_PLANTING" 0 ((6572.39819 938.91403) (6576.16867 931.37161) (6583.71041 927.60181)))
("SF_SOLAR" 0 ((6576.16867 7960.03020) (6579.93993 7952.48869)))
("SF_PLANTING" 0 ((6576.16867 4049.77376) (6583.71041 4049.77376)))
("SF_PLANTING" 0 ((6591.25215 4128.95928) (6572.54593 4072.39819) (6576.16867 4049.77376)))
("SF_PLANTING" 0 ((6576.16867 3868.77828) (6598.79310 3865.00713)))
("SF_PLANTING" 0 ((6576.16867 3868.77828) (6576.31719 3887.63156) (6583.85882 3902.56029) (6591.25215 3906.33111)
(6610.10532 3906.48609)))
("SF_SOLAR" 0 ((6602.56437 7858.22025) (6579.93993 7884.61538)))
("SF_PLANTING" 0 ((6591.25215 4023.37817) (6590.05419 4038.46154) (6583.71041 4049.77376)))
("SF_PLANTING" 0 ((6666.66640 4102.56369) (6644.04197 4097.58903) (6625.18880 4083.56233) (6602.41584 4058.51957)
(6583.71041 4049.77376)))
("SF_PLANTING" 0 ((6583.71041 904.97738) (6583.71041 927.60181)))
("SF_PLANTING" 0 ((6640.27149 950.22624) (6621.41753 942.83224) (6602.56437 941.48043) (6583.71041 927.60181)))
("SF_PLANTING" 0 ((6583.71041 904.97738) (6602.56437 901.21244) (6651.58371 904.82274) (6659.11855 901.05226)
(6666.51176 889.89536) (6662.67568 856.32670) (6647.81324 854.76007) (6632.43360 844.94197) (6636.49480 705.12726)
(6632.87749 690.04525) (6632.58201 603.32489) (6628.95928 595.77771)))
("SF_PLANTING" 0 ((6587.48088 6881.59853) (6602.56437 6895.62557) (6632.72975 6910.70871) (6659.11855 6911.61640)
(6666.66640 6907.99423)))
("SF_PLANTING" 0 ((6610.10532 6779.78857) (6598.79310 6765.91018) (6587.48088 6764.70588)))
("SF_PLANTING" 0 ((6587.48088 6723.22749) (6594.87489 6696.83258) (6595.02262 6561.08597)))
("SF_PLANTING" 0 ((6870.28631 6730.76923) (6794.87206 6730.62093) (6779.78857 6727.01188) (6764.70588 6730.62093)
(6723.22749 6730.76267) (6704.37432 6727.00532) (6598.79310 6726.85045) (6587.48088 6723.22749)))
("SF_PLANTING" 0 ((6587.48088 452.48869) (6596.22059 429.86425) (6621.26912 392.15781) (6616.44910 369.53824)
(6602.56437 361.99095)))
("SF_ARCHITECTURE" 0 ((6595.02262 5527.90305) (6595.01640 4283.55916) (6591.40679 4268.47704) (6595.01640 4219.45701)
(6591.39989 4204.37364) (6591.25215 4128.95928)))
("SF_PLANTING" 0 ((6591.25215 4128.95928) (6610.10532 4129.10735) (6636.50102 4137.69197) (6650.52738 4147.96097)
(6662.89593 4174.20814)))
("SF_PLANTING" 0 ((6591.25215 4023.37817) (6610.10532 4028.34695) (6628.95928 4041.32410) (6659.12545 4053.54491)))
("SF_PLANTING" 0 ((6670.43767 3812.21719) (6644.04197 3798.19016) (6625.18880 3793.51176) (6598.80000 3793.51787)
(6591.25215 3800.90498)))
("SF_PLANTING" 0 ((6598.79310 3865.00713) (6598.64536 3823.52941) (6591.25215 3800.90498)))
("SF_SOLAR" 0 ((6598.79310 8069.38167) (6595.02262 8080.69389)))
("SF_PLANTING" 0 ((6632.72998 6474.35905) (6602.57059 6479.33405) (6596.22681 6485.67783) (6595.02262 6561.08597)))
("SF_ARCHITECTURE" 0 ((6595.02262 5527.90305) (6625.18880 5539.06742) (6644.04197 5539.06742) (6662.89593 5531.67421)))
("SF_SOLAR" 0 ((6598.79310 8031.67421) (6598.79310 8020.36199)))
("SF_PLANTING" 0 ((6598.79310 3865.00713) (6613.87658 3865.00713)))
("SF_MASONRY_AND_ARCH" 0 ((6606.33484 2756.41052) (6598.79310 2756.41052)))
("SF_MASONRY_AND_ARCH" 0 ((6602.56437 2273.75566) (6602.56437 2311.46278)))
("SF_MASONRY_AND_ARCH" 0 ((6602.56437 2311.46278) (6617.64706 2315.22783) (6817.48959 2315.38869) (6823.83337
2319.15916) (6825.03744 2330.31674)))
("SF_MASONRY_AND_ARCH" 0 ((6783.55984 2273.75566) (6757.16414 2269.98518) (6617.64706 2269.99140) (6602.56437
2273.75566)))
("SF_MASONRY_AND_ARCH" 0 ((6685.52036 1907.99423) (6602.56437 1907.99423)))
("SF_MASONRY_AND_ARCH" 0 ((6689.29084 1674.20814) (6602.56437 1670.43835)))
("SF_PLANTING" 0 ((6602.56437 343.13631) (6602.56437 361.99095)))
("SF_PLANTING" 0 ((6602.56437 343.13631) (6636.50102 325.33326) (6666.66640 316.74208)))
("SF_MASONRY_AND_ARCH" 0 ((6606.33484 2220.96505) (6613.88281 2224.58857) (6636.49412 2223.53213) (6642.98563
2217.18767) (6647.81324 2202.11188)))
("SF_MASONRY_AND_ARCH" 0 ((6606.33484 1742.08145) (6613.88281 1745.70419) (6677.97862 1745.99966) (6696.83258
1753.39367)))
("SF_PLANTING" 0 ((6606.33484 1263.19853) (6613.88281 1270.58484) (6636.50102 1274.21380) (6647.81324 1270.73812)))
("SF_PLANTING" 0 ((6625.18880 1142.53394) (6606.33484 1134.99152)))
("SF_PLANTING" 0 ((6606.33484 1003.01753) (6607.53903 988.08111) (6632.57511 969.08088) (6640.27149 950.22624)))
("SF_PLANTING" 0 ((6606.33484 1003.01753) (6625.18880 1014.32975)))
("SF_SOLAR" 0 ((6610.10532 7918.55204) (6613.87658 7926.09355)))
("SF_PLANTING" 0 ((6610.10532 6779.78857) (6628.95928 6787.33032)))
("SF_PLANTING" 0 ((6613.87658 3865.00713) (6613.72885 3898.93756) (6610.10532 3906.48609)))
("SF_PLANTING" 0 ((6647.81324 3914.02715) (6628.95928 3913.87907) (6610.10532 3906.48609)))
("SF_PLANTING" 0 ((6610.10532 3231.52364) (6628.95928 3231.52364)))
("SF_PLANTING" 0 ((6610.10532 3231.52364) (6606.48948 3205.12794) (6610.25995 3197.59321) (6621.41753 3190.04525)))
("SF_MASONRY_AND_ARCH" 0 ((6610.10532 2085.21844) (6632.72975 2086.27489) (6644.03575 2092.90792) (6651.58371
2104.07240)))
("SF_MASONRY_AND_ARCH" 0 ((6870.28631 1987.17975) (6696.83948 1987.33439) (6690.49502 1991.10486) (6685.36572
2019.91844) (6647.81324 2027.46640) (6610.10532 2028.65735)))
("SF_MASONRY_AND_ARCH" 0 ((6700.60305 1436.65158) (6677.97862 1433.02885) (6610.10532 1432.88179)))
("SF_MASONRY_AND_ARCH" 0 ((6783.55984 1334.84163) (6753.39367 1338.60656) (6677.97862 1334.84163) (6610.10532
1338.61143)))
("SF_PLANTING" 0 ((6621.41753 516.59219) (6610.10532 524.13179)))
("SF_PLANTING" 0 ((6662.89593 3831.07048) (6621.42443 3863.80328) (6613.87658 3865.00713)))
("SF_MASONRY_AND_ARCH" 0 ((6681.74989 2960.03043) (6625.18880 2960.17817) (6613.87658 2963.80090)))
("SF_MASONRY_AND_ARCH" 0 ((6613.87658 2963.80090) (6621.41753 3190.04525)))
("SF_SOLAR" 0 ((6621.41753 8114.63054) (6617.64706 8133.48416)))
("SF_SOLAR" 0 ((6825.03744 7839.36652) (6617.64706 7839.36652)))
("SF_SOLAR" 0 ((6621.41753 8190.04525) (6625.18880 8163.65000)))
("SF_SOLAR" 0 ((6621.41753 8084.46448) (6621.41753 8076.92308)))
("SF_SOLAR" 0 ((6621.41753 7952.48869) (6621.41753 7960.03020)))
("SF_PLANTING" 0 ((6621.41753 3190.04525) (6632.57511 3205.12794) (6628.95928 3231.52364)))
("SF_PLANTING" 0 ((6621.41753 516.59219) (6646.76369 437.40667) (6659.12545 373.30317)))
("SF_PLANTING" 0 ((6621.41753 516.59219) (6644.04197 539.21663)))
("SF_SOLAR" 0 ((6625.18880 8163.65000) (6665.61697 8114.63054) (6750.67262 7982.65452) (6798.79027 7918.55204)
(6817.49649 7900.90260) (6836.34966 7899.69830)))
("SF_PLANTING" 0 ((6625.18880 1021.86934) (6625.18880 1014.32975)))
("SF_PLANTING" 0 ((6625.18880 1014.32975) (6632.72975 1010.55713)))
("SF_PLANTING" 0 ((6734.53971 6776.01810) (6715.68654 6787.18201) (6647.81324 6783.55984) (6628.95928 6787.33032)))
("SF_PLANTING" 0 ((6628.95928 6787.33032) (6636.50102 6832.57919)))
("SF_PLANTING" 0 ((6685.52036 3239.06482) (6674.20814 3239.06482) (6640.27149 3239.06482) (6628.95928 3231.52364)))
("SF_SOLAR" 0 ((6632.72975 7869.53247) (6651.58371 7869.53247)))
("SF_ARCHITECTURE" 0 ((6632.72975 6048.26538) (6633.78620 6021.87036) (6644.04197 6006.78733)))
("SF_PLANTING" 0 ((6632.72998 6474.35905) (6632.72975 6048.26538)))
("SF_PLANTING" 0 ((6632.72998 6474.35905) (6655.35419 6481.89389) (6685.52036 6478.13620) (6715.68654 6481.89389)
(6828.80871 6481.90045) (6847.66188 6478.27771) (6924.96256 6478.12964)))
("SF_PLANTING" 0 ((6666.66640 6907.99423) (6665.46233 6892.91109) (6641.46946 6870.28631) (6636.64876 6855.20362)
(6636.50102 6832.57919)))
("SF_PLANTING" 0 ((6674.20814 6836.34966) (6636.50102 6832.57919)))
("SF_MASONRY_AND_ARCH" 0 ((6651.58371 2639.51708) (6650.37952 2658.21640) (6640.27149 2662.14152)))
("SF_PLANTING" 0 ((6704.37432 931.37161) (6674.20814 945.40554) (6640.27149 950.22624)))
("SF_SOLAR" 0 ((6662.89593 8095.77670) (6651.58993 8096.97443) (6644.04197 8103.31833)))
("SF_SOLAR" 0 ((6651.58371 8110.85973) (6644.04197 8103.31833)))
("SF_SOLAR" 0 ((6644.04197 8084.46448) (6647.81324 8069.38167)))
("SF_SOLAR" 0 ((6644.04197 7982.65452) (6644.04197 7990.19615)))
("SF_SOLAR" 0 ((6644.04197 7952.48869) (6647.81324 7960.03020)))
("SF_MASONRY_AND_ARCH" 0 ((6644.04197 2567.87330) (6655.35419 2533.93665)))
("SF_MASONRY_AND_ARCH" 0 ((6644.04197 2567.87330) (6689.29084 2579.03778) (6794.87206 2586.72726)))
("SF_MASONRY_AND_ARCH" 0 ((6644.04197 1591.25283) (6644.04197 1583.71041)))
("SF_PLANTING" 0 ((6647.81324 3914.02715) (6655.50882 3900.14853) (6674.20814 3898.94378)))
("SF_PLANTING" 0 ((6666.66640 3929.11052) (6655.36109 3925.18473) (6647.81324 3914.02715)))
("SF_SOLAR" 0 ((6843.89140 7914.78133) (6784.61618 7993.96674) (6744.80249 8061.84005) (6651.58371 8197.58665)))
("SF_PLANTING" 0 ((6651.58371 7051.28179) (6662.89593 7045.84627) (6696.83258 7046.46188) (6760.93541 7014.77240)
(6772.24762 7013.57466)))
("SF_MASONRY_AND_ARCH" 0 ((6651.58371 2639.51708) (6677.97862 2635.75351) (6723.22749 2639.36934) (6794.87206
2631.97613) (6851.43314 2635.74661) (6892.91075 2632.12455) (6907.99423 2639.51708)))
("SF_MASONRY_AND_ARCH" 0 ((6651.58371 2115.38462) (6651.58371 2104.07240)))
("SF_MASONRY_AND_ARCH" 0 ((6659.12545 2104.07240) (6651.58371 2104.07240)))
("SF_PLANTING" 0 ((6651.58371 252.63857) (6670.43767 256.41120)))
("SF_PLANTING" 0 ((6674.20814 4023.37817) (6659.12545 4053.54491)))
("SF_PLANTING" 0 ((6666.66640 4068.62704) (6659.12545 4053.54491)))
("SF_PLANTING" 0 ((6659.12545 3996.98382) (6666.66640 3970.58824)))
("SF_PLANTING" 0 ((6674.20814 4023.37817) (6659.12545 3996.98382)))
("SF_MASONRY_AND_ARCH" 0 ((6659.12545 2156.86301) (6813.72523 2156.86301)))
("SF_PLANTING" 0 ((6670.43767 980.39310) (6662.89593 984.16290) (6659.12545 980.39310)))
("SF_PLANTING" 0 ((6672.32251 329.94061) (6664.16086 335.67681) (6660.17489 346.90894) (6659.12545 373.30317)))
("SF_PLANTING" 0 ((6689.29084 392.15781) (6666.67330 374.50803) (6659.12545 373.30317)))
("SF_ARCHITECTURE" 0 ((6662.89593 5659.87941) (6676.92229 5648.41912) (6681.74299 5633.48416) (6680.54570 5622.17195)
(6662.89593 5607.08857)))
("SF_ARCHITECTURE" 0 ((6662.89593 5659.87941) (6670.43767 5701.35747)))
("SF_ARCHITECTURE" 0 ((6662.89593 5607.08857) (6662.89593 5592.00645)))
("SF_ARCHITECTURE" 0 ((6662.89593 5592.00645) (6684.46403 5573.14570) (6689.29084 5554.29864) (6685.36572 5540.27195)
(6662.89593 5531.67421)))
("SF_ARCHITECTURE" 0 ((6662.89593 4174.20814) (6662.89593 5531.67421)))
("SF_PLANTING" 0 ((6715.68654 4136.50034) (6744.79559 4170.43699) (6752.18948 4189.28462) (6749.46154 4195.62183)
(6723.22749 4191.86414) (6689.29084 4171.49367) (6670.44389 4170.58541) (6662.89593 4174.20814)))
("SF_PLANTING" 0 ((6662.89593 3831.07048) (6662.89593 3823.52941) (6670.43767 3819.75826)))
("SF_PLANTING" 0 ((6662.89593 3831.07048) (6674.05973 3849.92500) (6674.20814 3898.94378)))
("SF_PLANTING" 0 ((6711.91527 6907.99423) (6666.66640 6907.99423)))
("SF_PLANTING" 0 ((6670.43767 4113.87590) (6666.66640 4121.41821)))
("SF_PLANTING" 0 ((6666.66640 4068.62704) (6666.66640 4102.56369)))
("SF_PLANTING" 0 ((6666.66640 4102.56369) (6670.43767 4113.87590)))
("SF_PLANTING" 0 ((6696.83258 4072.39819) (6666.66640 4068.62704)))
("SF_PLANTING" 0 ((6666.66640 3970.58824) (6704.37432 3966.81708)))
("SF_PLANTING" 0 ((6666.66640 3929.11052) (6666.66640 3970.58824)))
("SF_PLANTING" 0 ((6666.66640 3929.11052) (6689.29084 3929.11052)))
("SF_PLANTING" 0 ((6700.60305 1297.13518) (6666.66640 1285.82296)))
("SF_PLANTING" 0 ((6666.66640 316.74208) (6666.81414 275.27059) (6670.43767 267.72342)))
("SF_PLANTING" 0 ((6672.32251 329.94061) (6666.66640 316.74208)))
("SF_ARCHITECTURE" 0 ((6840.12093 5735.29412) (6838.91674 5708.90543) (6828.80871 5701.51210) (6798.64253 5705.12172)
(6689.29084 5705.12828) (6670.43767 5701.35747)))
("SF_PLANTING" 0 ((6670.43767 4113.87590) (6693.06210 4128.95928)))
("SF_PLANTING" 0 ((6670.43767 3812.21719) (6670.43767 3819.75826)))
("SF_PLANTING" 0 ((6670.43767 3819.75826) (6693.06210 3833.78495) (6726.99876 3838.61278)))
("SF_PLANTING" 0 ((6749.62319 3804.67613) (6734.53971 3793.51787) (6689.29774 3793.51787) (6670.43767 3812.21719)))
("SF_MASONRY_AND_ARCH" 0 ((6670.43767 1263.19762) (6945.70136 1263.19762) (7021.11640 1259.42590)))
("SF_PLANTING" 0 ((6670.43767 256.41120) (6670.43767 267.72342)))
("SF_PLANTING" 0 ((6726.99876 305.42986) (6708.14480 287.77387) (6689.29084 281.60747) (6670.43767 267.72342)))
("SF_PLANTING" 0 ((6670.43767 256.41120) (6689.29084 241.48167) (6726.99876 241.32636)))
("SF_PLANTING" 0 ((6672.32251 329.94061) (6674.20814 335.59672) (6680.80667 337.48020)))
("SF_PLANTING" 0 ((6672.32251 329.94061) (6680.80667 337.48020)))
("SF_PLANTING" 0 ((6674.20814 6836.34966) (6681.75611 6832.72749) (6734.53971 6832.72749) (6760.93541 6840.12093)))
("SF_PLANTING" 0 ((6674.20814 6836.34966) (6681.90452 6866.36753) (6693.06210 6873.00079) (6711.91527 6874.05758)))
("SF_PLANTING" 0 ((6674.20814 4023.37817) (6689.29084 4034.69038)))
("SF_PLANTING" 0 ((6674.20814 3898.94378) (6689.29084 3906.48609)))
("SF_PLANTING" 0 ((6708.14480 7006.03292) (6693.06210 7007.23722) (6677.97862 7017.34514)))
("SF_PLANTING" 0 ((6680.80667 337.48020) (6689.26052 329.47455) (6710.71120 339.51493) (6711.91527 373.30317)))
("SF_PLANTING" 0 ((6680.80667 337.48020) (6688.09299 361.99095) (6685.52036 373.30317)))
("SF_PLANTING" 0 ((6680.80667 337.48020) (6685.52036 339.36652)))
("SF_ARCHITECTURE" 0 ((6760.93541 5957.76765) (6681.74989 5991.70430)))
("SF_MASONRY_AND_ARCH" 0 ((6681.74989 2960.03043) (6711.91527 2960.03043)))
("SF_MASONRY_AND_ARCH" 0 ((6681.74989 2960.03043) (6681.75611 3171.19129) (6685.22421 3186.27477) (6681.75611
3220.21143) (6685.52036 3239.06482)))
("SF_SOLAR" 0 ((6685.52036 8031.67421) (6685.52036 8020.36199)))
("SF_PLANTING" 0 ((6711.91527 3239.06482) (6685.52036 3239.06482)))
("SF_MASONRY_AND_ARCH" 0 ((6689.29084 1900.45249) (6685.52036 1907.99423)))
("SF_MASONRY_AND_ARCH" 0 ((6685.52036 1907.99423) (6696.83258 1914.33111) (6813.72523 1911.76471)))
("SF_SOLAR" 0 ((6689.29084 8163.65000) (6855.20362 8163.49536) (6866.36810 8156.10192) (6896.68201 8114.63054)))
("SF_SOLAR" 0 ((6689.29084 7982.65452) (6689.29084 7990.19615)))
("SF_SOLAR" 0 ((6689.29084 7960.03020) (6689.29084 7952.48869)))
("SF_PLANTING" 0 ((6689.29084 3929.11052) (6689.29084 3906.48609)))
("SF_PLANTING" 0 ((6689.29084 3929.11052) (6699.54672 3936.65781) (6708.14480 3955.50486)))
("SF_PLANTING" 0 ((6719.45701 3898.94378) (6704.37432 3905.42941) (6689.29084 3906.48609)))
("SF_MASONRY_AND_ARCH" 0 ((6689.29084 1877.82805) (6693.06210 1858.97410)))
("SF_MASONRY_AND_ARCH" 0 ((6700.60305 1553.54355) (6699.39898 1561.09219) (6689.29084 1572.39819)))
("SF_PLANTING" 0 ((6832.57919 723.98190) (6806.18428 727.75170) (6700.60305 727.74683) (6689.29084 723.98190)))
("SF_PLANTING" 0 ((6689.29084 392.15781) (6708.14480 392.15781)))
("SF_PLANTING" 0 ((6689.29084 392.15781) (6690.49502 411.00962) (6700.60305 422.32183)))
("SF_SOLAR" 0 ((6704.37432 8099.54751) (6693.06210 8095.77670)))
("SF_PLANTING" 0 ((6719.45701 6923.07692) (6711.90905 6934.24118) (6693.06210 6945.70136)))
("SF_PLANTING" 0 ((6704.37432 592.00509) (6693.06210 592.00509)))
("SF_MASONRY_AND_ARCH" 0 ((6696.83258 1753.39367) (6715.68654 1749.62387) (6734.53971 1753.23903) (6749.62319
1749.77093) (6798.64253 1753.09751) (6817.49649 1749.63009) (6836.34966 1753.39367)))
("SF_MASONRY_AND_ARCH" 0 ((6866.51584 1813.72455) (6836.34966 1817.49027) (6704.38054 1816.29231) (6696.98722
1806.18495) (6696.83258 1753.39367)))
("SF_MASONRY_AND_ARCH" 0 ((6700.60305 1534.69174) (6708.15170 1527.30396) (6745.85192 1530.91912) (6836.34966
1527.30396) (6862.74536 1542.08360) (6930.61867 1538.46154) (6953.24310 1542.21889) (6968.32579 1538.75769) (7013.57466
1542.37975) (7028.65735 1549.77376)))
("SF_MASONRY_AND_ARCH" 0 ((6700.60305 1436.65158) (6700.60305 1459.27602)))
("SF_MASONRY_AND_ARCH" 0 ((6700.60305 1436.65158) (6719.45701 1432.88665) (6791.10079 1436.65158) (6821.26697
1432.88179)))
("SF_PLANTING" 0 ((6719.45701 411.00962) (6700.60305 422.32183)))
("SF_PLANTING" 0 ((6708.14480 437.40667) (6700.60305 429.86425) (6700.60305 422.32183)))
("SF_SOLAR" 0 ((6862.74536 8144.79638) (6847.66188 8141.02568) (6745.85192 8141.03213) (6719.45701 8144.64830)
(6704.37432 8137.25498)))
("SF_PLANTING" 0 ((6708.14480 3955.50486) (6704.37432 3966.81708)))
("SF_PLANTING" 0 ((6776.01810 3993.21267) (6782.50962 4004.52489) (6783.25667 4018.25509) (6745.85192 4014.63292)
(6719.60543 4000.59977) (6704.37432 3966.81708)))
("SF_MASONRY_AND_ARCH" 0 ((6704.37432 2104.07240) (6772.24762 2104.07240)))
("SF_SOLAR" 0 ((6711.91527 7982.65452) (6708.14480 7993.96674)))
("SF_PLANTING" 0 ((6715.68654 4136.50034) (6708.14480 4132.73043)))
("SF_PLANTING" 0 ((6768.47636 3981.90045) (6730.76923 3960.33201) (6708.14480 3955.50486)))
("SF_PLANTING" 0 ((6779.78857 1025.64197) (6719.45701 1029.56640) (6708.14480 1036.95419)))
("SF_PLANTING" 0 ((6711.91527 373.30317) (6708.14480 392.15781)))
("SF_PLANTING" 0 ((6719.45701 411.00962) (6708.14480 392.15781)))
("SF_PLANTING" 0 ((6711.91527 6907.99423) (6711.91527 6874.05758)))
("SF_PLANTING" 0 ((6719.45701 6923.07692) (6719.45701 6915.53518) (6711.91527 6907.99423)))
("SF_PLANTING" 0 ((6719.45701 6866.51584) (6711.91527 6874.05758)))
("SF_PLANTING" 0 ((6711.91527 4102.56369) (6719.30860 4121.41821) (6715.68654 4136.50034)))
("SF_MASONRY_AND_ARCH" 0 ((6711.91527 3239.06482) (6711.92149 3099.54751) (6715.68654 3076.92308) (6715.68032
2975.11312) (6711.91527 2960.03043)))
("SF_PLANTING" 0 ((6711.91527 3239.06482) (6734.53971 3242.82896) (6760.93541 3235.29412)))
("SF_MASONRY_AND_ARCH" 0 ((6711.91527 2960.03043) (6730.76923 2956.25916) (6760.93541 2960.03043)))
("SF_PLANTING" 0 ((6711.91527 373.30317) (6749.62319 373.30317)))
("SF_PLANTING" 0 ((6832.57919 837.10407) (6821.26697 833.48133) (6764.70588 833.18586) (6734.53971 822.16980)
(6715.68654 822.02206)))
("SF_PLANTING" 0 ((6719.45701 6923.07692) (6742.08145 6926.84740)))
("SF_PLANTING" 0 ((6723.22749 3883.86165) (6719.45701 3887.63156) (6719.45701 3898.94378)))
("SF_PLANTING" 0 ((6719.45701 3898.94378) (6734.53971 3910.25600)))
("SF_PLANTING" 0 ((6825.03744 1093.51527) (6734.53971 1093.35995) (6727.00498 1089.58937) (6719.45701 1078.43043)))
("SF_PLANTING" 0 ((6719.45701 411.00962) (6738.31097 418.39740) (6749.61629 417.34717) (6759.87896 403.47002)
(6760.93541 384.61538)))
("SF_PLANTING" 0 ((6734.53971 6776.01810) (6723.22749 6753.39367)))
("SF_PLANTING" 0 ((6723.22749 3883.86165) (6723.37523 3849.92500) (6726.99876 3838.61278)))
("SF_PLANTING" 0 ((6723.22749 3883.86165) (6742.08145 3887.63156)))
("SF_SOLAR" 0 ((6726.99876 8107.08891) (6757.16414 8099.70215) (6772.24762 8103.17025) (6900.45249 8105.88462)
(6919.30645 8095.77670)))
("SF_PLANTING" 0 ((6749.62319 3804.67613) (6741.02511 3834.68699) (6726.99876 3838.61278)))
("SF_PLANTING" 0 ((6726.99876 241.32636) (6734.54661 233.94005) (6798.63563 233.93382) (6806.18428 237.55656)))
("SF_PLANTING" 0 ((6783.55984 297.88744) (6760.93541 276.32014) (6738.45871 263.80373) (6726.99876 241.32636)))
("SF_ARCHITECTURE" 0 ((6730.76923 4464.55464) (6934.38914 4464.56154) (6968.32579 4468.17771) (6994.72070 4453.24287)))
("SF_MASONRY_AND_ARCH" 0 ((6817.49649 1165.15837) (6798.64253 1168.92817) (6738.31719 1168.78111) (6730.76923
1165.15837)))
("SF_SOLAR" 0 ((6734.53971 8133.48416) (6738.31097 8122.17195)))
("SF_SOLAR" 0 ((6734.53971 7960.03020) (6734.53971 7952.48869)))
("SF_PLANTING" 0 ((6734.53971 6776.01810) (6764.70588 6783.55984)))
("SF_PLANTING" 0 ((6749.62319 3898.94378) (6734.53971 3910.25600)))
("SF_PLANTING" 0 ((6821.26697 3906.48609) (6817.34186 3916.74785) (6791.10079 3932.72647) (6745.85192 3934.39762)
(6735.74389 3925.33937) (6734.53971 3910.25600)))
("SF_PLANTING" 0 ((6855.20362 776.77319) (6832.57919 773.29751) (6821.26697 776.61787) (6806.18428 773.29751)
(6794.87206 776.62477) (6734.53971 776.77319)))
("SF_ARCHITECTURE" 0 ((6990.95023 5625.94276) (6983.40226 5633.32296) (6964.55532 5629.71991) (6832.57919 5629.71335)
(6806.18428 5633.48416) (6738.31097 5625.94276)))
("SF_MASONRY_AND_ARCH" 0 ((6855.20362 2786.57590) (6857.77964 2767.72274) (6851.72930 2756.56516) (6757.16414
2760.18100) (6738.31097 2756.41052)))
("SF_PLANTING" 0 ((6802.41301 373.30317) (6793.82251 422.32183) (6778.11708 456.25848) (6774.81391 486.27070)
(6768.47014 490.04186) (6753.39367 490.04186) (6738.31097 478.88292)))
("SF_PLANTING" 0 ((6768.47636 3880.09050) (6749.62941 3880.24514) (6742.08145 3887.63156)))
("SF_PLANTING" 0 ((6749.62319 3898.94378) (6742.08145 3887.63156)))
("SF_MASONRY_AND_ARCH" 0 ((6760.93541 2960.03043) (6772.09299 2944.94695) (6772.09989 2911.01029) (6764.55124
2893.36120) (6745.85192 2892.15713)))
("SF_MASONRY_AND_ARCH" 0 ((6813.72523 1334.84163) (6821.56312 1342.53111) (6817.34186 1364.85317) (6809.95475
1368.62364) (6757.16414 1369.83462) (6747.04989 1376.46776) (6745.85192 1395.17251)))
("SF_ARCHITECTURE" 0 ((6749.62319 5588.23529) (6983.40848 5588.22907) (6994.72070 5584.46414)))
("SF_PLANTING" 0 ((6768.47636 3895.17387) (6749.62319 3898.94378)))
("SF_PLANTING" 0 ((6749.62319 3804.67613) (6772.24762 3797.28224) (6825.03744 3795.24887)))
("SF_PLANTING" 0 ((6783.55984 297.88744) (6765.76222 320.51188) (6754.45000 343.13631) (6749.62319 373.30317)))
("SF_PLANTING" 0 ((6749.62319 373.30317) (6753.39367 380.84559) (6760.93541 384.61538)))
("SF_MASONRY_AND_ARCH" 0 ((6753.39367 1670.43835) (6783.55984 1670.43835)))
("SF_MASONRY_AND_ARCH" 0 ((6753.39367 1466.81844) (6772.24762 1466.81844)))
("SF_SOLAR" 0 ((6757.16414 8133.48416) (6757.16414 8122.17195)))
("SF_SOLAR" 0 ((6757.16414 8058.06946) (6806.18428 8061.83348) (6930.61867 8061.68541) (6940.88133 8054.29197)
(6968.32579 8012.82059)))
("SF_SOLAR" 0 ((6764.70588 7914.78133) (6757.16414 7926.09355)))
("SF_PLANTING" 0 ((6757.16414 6979.63801) (6783.55984 6964.55532)))
("SF_PLANTING" 0 ((6760.93541 6840.12093) (6764.70588 6828.80871)))
("SF_PLANTING" 0 ((6809.95475 6919.30645) (6805.81550 6886.41923) (6768.62489 6855.05532) (6760.93541 6840.12093)))
("SF_MASONRY_AND_ARCH" 0 ((6760.93541 2960.03043) (6757.16414 2982.65486) (6760.63914 3009.04977) (6757.31188
3020.36199) (6757.16414 3069.38133) (6760.92919 3092.00577) (6760.93541 3235.29412)))
("SF_PLANTING" 0 ((6760.93541 3235.29412) (6783.55294 3240.26878) (6791.10102 3250.37681) (6791.10102 3589.74333)))
("SF_PLANTING" 0 ((6760.93541 599.54751) (6760.93541 539.21663)))
("SF_PLANTING" 0 ((6802.41301 373.30317) (6760.93541 384.61538)))
("SF_PLANTING" 0 ((6764.70588 6783.55984) (6764.70588 6828.80871)))
("SF_PLANTING" 0 ((6855.20362 6840.12093) (6825.03744 6839.97262) (6764.70588 6828.80871)))
("SF_PLANTING" 0 ((6764.70588 6783.55984) (6772.25385 6779.93688) (6847.66188 6779.64072) (6862.74536 6776.01810)))
("SF_PLANTING" 0 ((6768.47636 3880.09050) (6768.47636 3895.17387)))
("SF_PLANTING" 0 ((6768.47636 3895.17387) (6806.18428 3899.09219) (6821.26697 3906.48609)))
("SF_PLANTING" 0 ((6768.47636 3880.09050) (6776.02500 3869.83495) (6794.87206 3865.00713)))
("SF_PLANTING" 0 ((6798.64253 6983.40848) (6783.70758 6994.72104) (6772.24762 7013.57466)))
("SF_PLANTING" 0 ((6885.36980 6998.49197) (6881.44389 7013.41980) (6862.89310 7024.89344) (6828.80871 7069.98744)
(6776.02500 7096.22805) (6768.63100 7088.98281) (6768.62489 7070.13575) (6779.64084 7039.96957) (6778.59072 7021.12296)
(6772.24762 7013.57466)))
("SF_MASONRY_AND_ARCH" 0 ((6866.51584 2820.51256) (6855.20362 2816.88982) (6779.79548 2816.59434) (6772.24762
2812.97161)))
("SF_SOLAR" 0 ((6776.01810 8069.38167) (6779.78857 8088.23529)))
("SF_ARCHITECTURE" 0 ((6798.64253 5923.83100) (6790.95305 5938.90747) (6779.78857 5946.45543)))
("SF_PLANTING" 0 ((6783.55984 6923.07692) (6809.95475 6919.30645)))
("SF_PLANTING" 0 ((6783.55984 297.88744) (6798.64253 297.88744)))
("SF_SOLAR" 0 ((6938.15962 8042.98643) (6923.07692 8039.22217) (6828.80871 8039.22217) (6787.33032 8046.75724)))
("SF_SOLAR" 0 ((6791.10079 8009.04977) (6802.41301 8005.28552) (6858.97410 8009.04977) (6934.38914 8008.90181)
(6953.24310 8005.28575) (6968.32579 8012.82059)))
("SF_ARCHITECTURE" 0 ((6791.10102 3589.74333) (7907.23982 3589.73710) (7926.09446 3585.97285)))
("SF_PLANTING" 0 ((6791.10102 3589.74333) (6791.10102 3717.94830) (6798.64943 3729.10656) (6823.83959 3744.49197)
(6826.70905 3755.65611) (6825.03744 3795.24887)))
("SF_PLANTING" 0 ((6889.14027 3797.13382) (6882.49412 3819.75826) (6870.28631 3833.79186) (6836.34966 3852.64570)
(6794.87206 3865.00713)))
("SF_PLANTING" 0 ((6794.87206 3865.00713) (6796.07613 3846.15385) (6816.44005 3823.52941) (6825.03744 3795.24887)))
("SF_SOLAR" 0 ((6802.41301 8024.13281) (6798.64253 8031.67421)))
("SF_PLANTING" 0 ((6798.64253 6983.40848) (6799.84672 6964.55532) (6828.80871 6926.84740)))
("SF_PLANTING" 0 ((6798.64253 6983.40848) (6806.18428 6984.61278) (6821.26697 6998.49197)))
("SF_ARCHITECTURE" 0 ((6825.03744 5844.64548) (6842.83507 5871.04072) (6842.83507 5904.97738) (6832.57296 5918.86256)
(6798.64253 5923.83100)))
("SF_PLANTING" 0 ((6798.64253 297.88744) (6806.02964 286.57523) (6806.18428 237.55656)))
("SF_PLANTING" 0 ((6798.64253 297.88744) (6809.95475 316.74208)))
("SF_SOLAR" 0 ((6802.41301 8088.23529) (6802.41301 8069.38167)))
("SF_MASONRY_AND_ARCH" 0 ((6828.80871 1025.64197) (6802.41301 1025.64197)))
("SF_PLANTING" 0 ((6802.41301 373.30317) (6809.95475 369.53337)))
("SF_PLANTING" 0 ((6821.26697 6998.49197) (6806.18428 7043.74084)))
("SF_PLANTING" 0 ((6907.99423 256.41120) (6900.44559 250.06674) (6877.82805 247.81244) (6847.66188 233.93450)
(6813.73213 233.93382) (6806.18428 237.55656)))
("SF_PLANTING" 0 ((6828.80871 6926.84740) (6821.26075 6920.50396) (6809.95475 6919.30645)))
("SF_MASONRY_AND_ARCH" 0 ((7138.00905 2273.75566) (7119.15509 2277.51991) (7039.96957 2277.51991) (7024.88688
2274.05181) (7002.26244 2281.14966) (6960.78405 2281.29118) (6889.14027 2274.95362) (6836.34966 2277.37771) (6809.95475
2269.98518)))
("SF_PLANTING" 0 ((6809.95475 369.53337) (6809.95475 316.74208)))
("SF_PLANTING" 0 ((6809.95475 369.53337) (6823.98111 384.61538) (6837.40611 422.17477) (6855.05588 433.78247)
(6870.28631 452.12070) (6888.98563 451.28382) (6900.45939 434.83891) (6915.53518 433.63405)))
("SF_PLANTING" 0 ((6858.97410 328.05430) (6832.57919 316.89050) (6809.95475 316.74208)))
("SF_MASONRY_AND_ARCH" 0 ((6813.72523 2156.86301) (6813.87296 2119.16199) (6817.49649 2111.61414)))
("SF_MASONRY_AND_ARCH" 0 ((6813.72523 2156.86301) (6851.43314 2160.62726) (6907.99423 2156.86301) (6926.84740
2160.48575) (7009.80419 2160.78812) (7019.91222 2168.18145) (7021.11640 2183.25792)))
("SF_SOLAR" 0 ((6817.49649 7971.34231) (6990.95023 7971.18767) (7002.11471 7963.79434) (7036.19910 7914.78133)))
("SF_MASONRY_AND_ARCH" 0 ((6817.49649 1466.81844) (6821.11923 1459.26912) (6821.26697 1432.88179)))
("SF_MASONRY_AND_ARCH" 0 ((6821.26697 1146.30373) (6817.49649 1165.15837)))
("SF_MASONRY_AND_ARCH" 0 ((6949.47183 1165.15837) (6938.15962 1168.78111) (6851.43314 1169.07658) (6840.12093
1172.54548) (6817.49649 1165.15837)))
("SF_PLANTING" 0 ((6870.28631 6979.63801) (6843.89140 6984.60622) (6828.81493 6997.28767) (6821.26697 6998.49197)))
("SF_PLANTING" 0 ((6874.05758 3895.17387) (6843.89140 3906.33767) (6821.26697 3906.48609)))
("SF_MASONRY_AND_ARCH" 0 ((6983.40848 3186.27477) (6972.09627 3182.50973) (6821.26697 3182.50351)))
("SF_MASONRY_AND_ARCH" 0 ((6821.26697 3114.63020) (6885.36980 3114.63020)))
("SF_MASONRY_AND_ARCH" 0 ((6828.80871 1410.25735) (6821.26697 1432.88179)))
("SF_PLANTING" 0 ((6821.26697 584.46550) (6836.34966 588.23529) (6926.84740 588.22907) (6945.70136 584.46550)))
("SF_SOLAR" 0 ((6825.03744 8133.48416) (6825.03744 8118.40113)))
("SF_SOLAR" 0 ((6825.03744 8069.38167) (6825.03744 8084.46448)))
("SF_SOLAR" 0 ((6828.80871 7982.65452) (6825.03744 7993.96674)))
("SF_ARCHITECTURE" 0 ((6825.03744 5844.64548) (6843.73676 5818.25045) (6842.68722 5799.39661) (6832.57919 5784.31380)))
("SF_PLANTING" 0 ((6889.14027 3797.13382) (6877.82805 3793.37014) (6825.03744 3795.24887)))
("SF_MASONRY_AND_ARCH" 0 ((6825.03744 2903.46934) (6832.58609 2896.08224) (6855.26097 2896.15339) (6861.32647
2900.68201) (6858.97410 2907.23982)))
("SF_MASONRY_AND_ARCH" 0 ((6825.03744 2345.39943) (6821.56312 2375.56561) (6836.34966 2424.58495)))
("SF_MASONRY_AND_ARCH" 0 ((6828.80871 1025.64197) (6832.43077 1067.11821) (6825.03744 1093.51527)))
("SF_MASONRY_AND_ARCH" 0 ((6825.03744 1093.51527) (6911.76471 1101.05486)))
("SF_PLANTING" 0 ((6828.80871 6926.84740) (6843.89140 6926.84740)))
("SF_MASONRY_AND_ARCH" 0 ((7209.65283 2971.34265) (7183.25792 2975.10690) (7070.13575 2971.34265) (7047.51131
2975.10690) (6828.80871 2975.11312)))
("SF_MASONRY_AND_ARCH" 0 ((6828.80871 1025.64197) (6836.34966 1021.86934)))
("SF_ARCHITECTURE" 0 ((6840.12093 5735.29412) (6842.69344 5742.84208) (6839.96629 5765.45995) (6832.57919 5784.31380)))
("SF_MASONRY_AND_ARCH" 0 ((6832.57919 2469.83382) (6850.37670 2473.75973) (6855.20362 2496.22952)))
("SF_MASONRY_AND_ARCH" 0 ((6836.34966 965.30826) (6828.96957 972.85690) (6832.57919 984.16290)))
("SF_PLANTING" 0 ((6832.57919 863.49830) (6832.57919 837.10407)))
("SF_PLANTING" 0 ((6832.57919 837.10407) (6851.43314 833.33428) (6881.59853 837.10407) (7017.34514 833.33914)
(7036.19910 837.10407)))
("SF_PLANTING" 0 ((6832.57919 723.98190) (6832.57919 686.27545)))
("SF_PLANTING" 0 ((6832.57919 723.98190) (6843.89140 727.60464) (6892.91075 723.98880) (6907.99423 727.75170)))
("SF_SOLAR" 0 ((6851.43314 7903.46912) (6847.66188 7899.69830) (6836.34966 7899.69830)))
("SF_SOLAR" 0 ((6843.89140 7914.78133) (6836.34966 7907.23982) (6836.34966 7899.69830)))
("SF_MASONRY_AND_ARCH" 0 ((6836.34966 1776.01810) (6836.34966 1753.39367)))
("SF_MASONRY_AND_ARCH" 0 ((7024.88688 1749.62387) (6885.36980 1738.31652) (6840.27557 1747.04231) (6836.34966
1753.39367)))
("SF_SOLAR" 0 ((6840.12093 7937.40577) (6934.38914 7937.41233) (6957.01357 7941.17647) (7009.80419 7937.40577)))
("SF_SOLAR" 0 ((6847.66188 7993.96674) (6843.89140 7986.42534)))
("SF_SOLAR" 0 ((6843.89140 7914.78133) (6851.43314 7903.46912)))
("SF_SOLAR" 0 ((6843.89140 7888.38609) (6866.51584 7850.67873)))
("SF_PLANTING" 0 ((6855.20362 6900.45249) (6848.85984 6904.37783) (6843.89140 6926.84740)))
("SF_PLANTING" 0 ((6881.59853 6938.15962) (6866.51584 6937.11018) (6843.89140 6926.84740)))
("SF_SOLAR" 0 ((6847.66188 8118.40113) (6847.66188 8133.48416)))
("SF_SOLAR" 0 ((6847.66188 8031.67421) (6847.66188 8020.36199)))
("SF_SOLAR" 0 ((6847.66188 7960.03020) (6851.43314 7948.71799)))
("SF_ARCHITECTURE" 0 ((6847.66188 3650.07545) (6862.74536 3650.07545) (7892.15781 3650.07545) (7907.23982 3650.07545)))
("SF_PLANTING" 0 ((6847.66188 3525.64129) (6964.55532 3525.64129)))
("SF_MASONRY_AND_ARCH" 0 ((7175.71618 3257.91855) (7051.28179 3256.40170) (7028.65735 3272.84661) (6983.40848
3269.52692) (6904.22296 3276.77251) (6862.74536 3276.62477) (6847.66188 3273.00124)))
("SF_SOLAR" 0 ((6851.43314 7903.46912) (7039.96957 7903.46256) (7062.59400 7899.69830) (7213.42410 7903.46256)
(7232.27726 7899.70486) (7383.10735 7899.55023) (7394.41957 7895.92760)))
("SF_PLANTING" 0 ((6855.20362 3427.60181) (6858.82568 3401.20690) (6851.43314 3382.35294)))
("SF_PLANTING" 0 ((6855.20362 6900.45249) (6860.03054 6885.36980) (6870.28631 6874.05758)))
("SF_PLANTING" 0 ((6855.20362 6900.45249) (6862.75158 6906.79649) (6881.59853 6911.76471)))
("SF_PLANTING" 0 ((6855.20362 6840.12093) (6862.59762 6821.26697) (6862.74536 6776.01810)))
("SF_PLANTING" 0 ((6855.20362 6840.12093) (6869.22998 6862.74502) (6870.28631 6874.05758)))
("SF_PLANTING" 0 ((6858.97410 6689.29084) (6847.81041 6662.89593) (6847.81652 6644.04887) (6855.20362 6636.50102)))
("SF_PLANTING" 0 ((6855.20362 3450.22624) (6852.78563 3465.15430) (6858.98100 3468.92557) (6885.36980 3472.84378)
(6907.99423 3469.09333) (6923.07692 3472.70294) (6972.09627 3472.85068)))
("SF_MASONRY_AND_ARCH" 0 ((6855.20362 2496.22952) (6862.75158 2499.85226) (6923.07692 2500.14774) (6938.15962
2503.76425) (6964.55532 2500.01312) (7126.69683 2500.00622) (7149.32127 2505.44208) (7209.65283 2503.62206) (7228.50679
2496.22952)))
("SF_PLANTING" 0 ((6945.70136 3340.87455) (6870.28631 3341.02919) (6858.97410 3352.18676)))
("SF_PLANTING" 0 ((6889.14027 328.05430) (6877.82805 324.29072) (6858.97410 328.05430)))
("SF_PLANTING" 0 ((6870.28631 414.78224) (6869.22998 399.69740) (6859.12873 380.84559) (6858.97410 328.05430)))
("SF_PLANTING" 0 ((6862.74536 6776.01810) (6870.28631 6776.01810)))
("SF_MASONRY_AND_ARCH" 0 ((6862.74536 1662.89593) (6877.82805 1674.05351) (7017.34514 1674.20814)))
("SF_SOLAR" 0 ((6866.51584 7952.48869) (6870.28631 7963.80090)))
("SF_PLANTING" 0 ((6866.51584 6557.31550) (6862.74536 6549.77376) (6866.51584 6542.23201)))
("SF_PLANTING" 0 ((6870.28631 6534.69106) (6866.51584 6542.23201)))
("SF_PLANTING" 0 ((6919.30645 6568.62771) (6866.51584 6542.23201)))
("SF_MASONRY_AND_ARCH" 0 ((6866.51584 2820.51256) (6866.51584 2865.76143)))
("SF_MASONRY_AND_ARCH" 0 ((6866.51584 2820.51256) (6885.36980 2816.74830) (7130.46731 2816.74830) (7145.55079
2820.21640) (7175.71618 2816.88982) (7209.49819 2828.20894) (7217.04683 2846.90826) (7217.19457 2865.76143)))
("SF_MASONRY_AND_ARCH" 0 ((6896.68201 1806.18495) (6877.82805 1806.33824) (6866.51584 1813.72455)))
("SF_MASONRY_AND_ARCH" 0 ((6870.28631 1828.80871) (6866.51584 1825.03744) (6866.51584 1813.72455)))
("SF_MASONRY_AND_ARCH" 0 ((7036.19910 1327.29921) (7021.11640 1334.69321) (6934.38914 1334.84785) (6915.53518
1338.60656) (6885.36980 1334.99627) (6866.51584 1338.61143)))
("SF_SOLAR" 0 ((6870.28631 8197.58665) (6877.82805 8186.27443)))
("SF_SOLAR" 0 ((6870.28631 8069.38167) (6870.28631 8084.46448)))
("SF_SOLAR" 0 ((6870.28631 7978.88394) (6870.28631 7990.19615)))
("SF_SOLAR" 0 ((7296.38009 7839.36652) (7269.98518 7835.59581) (6870.28631 7839.36652)))
("SF_PLANTING" 0 ((6870.28631 6979.63801) (6885.36980 6945.70136)))
("SF_PLANTING" 0 ((6870.28631 6979.63801) (6885.36980 6998.49197)))
("SF_PLANTING" 0 ((6870.28631 6874.05758) (6889.13337 6875.25509) (6896.68201 6881.59853)))
("SF_PLANTING" 0 ((6870.28631 6730.76923) (6870.28631 6776.01810)))
("SF_PLANTING" 0 ((6911.76471 6779.78857) (6870.28631 6776.01810)))
("SF_PLANTING" 0 ((6911.76471 6730.76923) (6870.28631 6730.76923)))
("SF_PLANTING" 0 ((6877.82805 6417.79796) (6874.05758 6417.79796) (6870.28631 6410.25633)))
("SF_MASONRY_AND_ARCH" 0 ((6870.28631 1987.17975) (6889.14027 1983.40848) (7013.57466 1987.17975)))
("SF_MASONRY_AND_ARCH" 0 ((6870.28631 1987.17975) (6871.49050 2013.56776) (6881.59853 2020.96176) (6930.61867
2021.26414) (6945.70136 2024.87998) (7009.80419 2021.11640)))
("SF_MASONRY_AND_ARCH" 0 ((6923.07692 1926.84740) (6911.76471 1929.42070) (6889.14027 1926.69898) (6871.34276
1915.52896) (6866.52206 1881.59853) (6866.66425 1847.66878) (6870.28631 1840.12093)))
("SF_MASONRY_AND_ARCH" 0 ((6870.28631 1414.02715) (6871.49050 1425.18473) (6877.83495 1428.95588) (6915.53518
1425.48778) (6994.72070 1436.50385) (7028.65735 1433.17726) (7047.51131 1436.65158)))
("SF_PLANTING" 0 ((6870.28631 648.56618) (6907.99423 648.56618)))
("SF_SOLAR" 0 ((7066.36527 7933.63495) (7052.33201 7948.71799) (6963.50509 8080.69389) (6904.07523 8159.87941)
(6889.14027 8173.75136) (6874.05758 8171.19163)))
("SF_SOLAR" 0 ((6874.05758 7918.55204) (6874.05758 7926.09355)))
("SF_ARCHITECTURE" 0 ((6874.05758 3710.40724) (6904.22296 3717.94876) (7918.55204 3717.94876) (7929.86425 3717.94876)))
("SF_PLANTING" 0 ((6915.53518 6606.33484) (6896.68201 6601.36007) (6877.82805 6583.71041)))
("SF_PLANTING" 0 ((6877.82805 6417.79796) (6885.36980 6417.79796)))
("SF_PLANTING" 0 ((6877.82805 6417.79796) (6885.36980 6440.42240)))
("SF_PLANTING" 0 ((6881.59853 6938.15962) (6881.59853 6911.76471)))
("SF_PLANTING" 0 ((6881.59853 6938.15962) (6885.36980 6945.70136)))
("SF_PLANTING" 0 ((6881.59853 6911.76471) (6896.68201 6881.59853)))
("SF_MASONRY_AND_ARCH" 0 ((6881.59853 2752.63925) (6892.91075 2756.40362) (6990.95023 2756.40430) (7006.03292
2752.79389) (7021.11640 2756.11425) (7051.28179 2748.86878)))
("SF_MASONRY_AND_ARCH" 0 ((6900.45249 1021.86934) (6881.59853 1018.09955)))
("SF_PLANTING" 0 ((6881.59853 486.42534) (6882.79649 493.97262) (6900.45249 520.36199)))
("SF_SOLAR" 0 ((6885.36980 7892.15690) (6885.36980 7884.61538)))
("SF_PLANTING" 0 ((6885.36980 6998.49197) (6896.53348 6994.56629) (6923.07692 6960.78405)))
("SF_PLANTING" 0 ((6923.07692 6949.47183) (6885.36980 6945.70136)))
("SF_SOLAR" 0 ((6889.14027 7918.55204) (6892.91075 7926.09355)))
("SF_ARCHITECTURE" 0 ((6889.14027 3797.13382) (7002.26244 3797.12760) (7024.88688 3793.36391) (7047.51131 3797.13382)))
("SF_PLANTING" 0 ((6904.22296 305.42986) (6889.14027 328.05430)))
("SF_PLANTING" 0 ((6889.14027 328.05430) (6893.06538 369.53337) (6900.45249 384.61538)))
("SF_SOLAR" 0 ((6892.91075 8141.02557) (6900.45249 8144.79638)))
("SF_SOLAR" 0 ((6892.91075 8080.69389) (6892.91075 8069.38167)))
("SF_SOLAR" 0 ((6892.91075 8031.67421) (6892.91075 8020.36199)))
("SF_SOLAR" 0 ((6892.91075 7978.88394) (6892.91075 7993.96674)))
("SF_SOLAR" 0 ((6892.91075 7960.03020) (6892.91075 7952.48869)))
("SF_PLANTING" 0 ((6892.91075 7081.44796) (6899.25452 7055.05305) (6896.68201 7043.74084)))
("SF_PLANTING" 0 ((6915.53518 6628.95928) (6892.91075 6644.04197)))
("SF_PLANTING" 0 ((6892.91075 395.92760) (6900.45249 384.61538)))
("SF_SOLAR" 0 ((6941.93088 7869.53247) (6896.68201 7869.53247)))
("SF_PLANTING" 0 ((6896.68201 6881.59853) (6934.38914 6881.59853)))
("SF_PLANTING" 0 ((6896.68201 6685.52036) (6911.76471 6693.06210)))
("SF_PLANTING" 0 ((6900.45249 6298.39106) (6911.75848 6311.00860) (6919.30645 6312.21719)))
("SF_ARCHITECTURE" 0 ((7892.15781 5833.33326) (7869.53337 5829.56267) (7801.66007 5833.33326) (7775.26301 5829.56923)
(7650.82862 5829.56923) (7628.20419 5833.33326) (7545.24887 5833.18507) (7530.16618 5829.56923) (7104.07240 5829.56923)
(7081.44796 5833.33326) (6911.76471 5829.56923) (6900.45249 5833.33326)))
("SF_ARCHITECTURE" 0 ((7051.28179 5795.62602) (7039.96957 5799.38348) (7024.88688 5795.92229) (7013.57466 5799.10034)
(6998.49197 5795.63258) (6900.45249 5795.62602)))
("SF_ARCHITECTURE" 0 ((6900.45249 5708.89887) (6915.53518 5712.66968) (6938.15962 5708.90543) (6987.17975 5712.52161)
(6998.49197 5708.89887)))
("SF_PLANTING" 0 ((6926.84740 388.38518) (6900.45249 384.61538)))
("SF_MASONRY_AND_ARCH" 0 ((6904.22296 3122.17195) (6914.33801 3118.24683) (6926.84740 3095.77704)))
("SF_PLANTING" 0 ((6907.99423 256.41120) (6900.60713 267.72342) (6904.22296 305.42986)))
("SF_PLANTING" 0 ((6938.15962 316.74208) (6904.22296 305.42986)))
("SF_MASONRY_AND_ARCH" 0 ((6907.99423 2647.05882) (6907.99423 2639.51708)))
("SF_MASONRY_AND_ARCH" 0 ((6960.78405 2639.51708) (6907.99423 2639.51708)))
("SF_PLANTING" 0 ((6907.99423 256.41120) (6915.53518 256.41120)))
("SF_SOLAR" 0 ((7092.76018 8163.65000) (6911.76471 8163.65000)))
("SF_PLANTING" 0 ((6911.76471 6779.78857) (6915.53518 6772.24762)))
("SF_PLANTING" 0 ((6923.07692 6828.80871) (6911.91244 6802.41301) (6911.76471 6779.78857)))
("SF_PLANTING" 0 ((6911.76471 6730.76923) (6911.76471 6693.06210)))
("SF_PLANTING" 0 ((6911.76471 6730.76923) (6915.53518 6738.31097)))
("SF_PLANTING" 0 ((6919.30645 6693.06210) (6911.76471 6693.06210)))
("SF_MASONRY_AND_ARCH" 0 ((7024.88688 2903.46912) (6911.76471 2903.46912)))
("SF_MASONRY_AND_ARCH" 0 ((6987.17975 1806.18495) (6911.76471 1806.18495)))
("SF_PLANTING" 0 ((6983.40848 788.08541) (6945.70136 787.93699) (6911.76471 780.54299)))
("SF_SOLAR" 0 ((6915.53518 7982.65452) (6915.53518 7993.96674)))
("SF_SOLAR" 0 ((6915.53518 7952.48869) (6915.53518 7963.80090)))
("SF_SOLAR" 0 ((6915.53518 7926.09355) (6915.53518 7914.78133)))
("SF_PLANTING" 0 ((6953.24310 6772.24762) (6915.53518 6772.24762)))
("SF_PLANTING" 0 ((6915.53518 6738.31097) (6915.53518 6772.24762)))
("SF_PLANTING" 0 ((6958.89921 6738.31097) (6915.53518 6738.31097)))
("SF_PLANTING" 0 ((6915.53518 6606.33484) (6915.53518 6628.95928)))
("SF_PLANTING" 0 ((6930.61867 6655.35419) (6925.64955 6640.27149) (6915.53518 6628.95928)))
("SF_PLANTING" 0 ((6915.53518 6606.33484) (6919.30645 6606.33484) (6919.30645 6602.56437)))
("SF_PLANTING" 0 ((6915.53518 6606.33484) (6919.30645 6602.56437)))
("SF_PLANTING" 0 ((6915.53518 256.41120) (6919.46109 249.00962) (6930.61867 242.38348) (6975.86753 241.32636)))
("SF_PLANTING" 0 ((6945.70136 286.57523) (6915.53518 256.41120)))
("SF_SOLAR" 0 ((6923.07692 8076.92308) (6919.30645 8095.77670)))
("SF_SOLAR" 0 ((6934.38914 8099.54751) (6919.30645 8095.77670)))
("SF_SOLAR" 0 ((6919.30645 8031.67421) (6923.07692 8027.90339) (6919.30645 8020.36199)))
("SF_PLANTING" 0 ((6949.47183 6689.29084) (6919.30645 6693.06210)))
("SF_PLANTING" 0 ((6919.30645 6693.06210) (6920.35588 6677.97862) (6930.61867 6655.35419)))
("SF_PLANTING" 0 ((6919.30645 6602.56437) (6953.24310 6602.56437)))
("SF_PLANTING" 0 ((6919.30645 6568.62771) (6915.54208 6583.71041) (6919.30645 6602.56437)))
("SF_PLANTING" 0 ((6919.30645 6568.62771) (6929.56844 6553.54423) (6934.38914 6534.69106)))
("SF_PLANTING" 0 ((6919.30645 6312.21719) (6925.79796 6308.29163) (6930.32240 6297.13416) (6924.27489 6278.28054)
(6926.84740 6263.19751)))
("SF_PLANTING" 0 ((6926.84740 6387.63190) (6923.22466 6380.08394) (6922.92919 6327.30023) (6919.30645 6312.21719)))
("SF_PLANTING" 0 ((6923.07692 6949.47183) (6923.07692 6960.78405)))
("SF_PLANTING" 0 ((6941.93088 7006.03292) (6937.10328 6979.63801) (6923.07692 6960.78405)))
("SF_PLANTING" 0 ((6938.15962 6945.70136) (6923.07692 6949.47183)))
("SF_PLANTING" 0 ((6924.96256 6478.12964) (6920.50430 6444.19299) (6923.07692 6406.48575)))
("SF_MASONRY_AND_ARCH" 0 ((6923.07692 2567.87330) (6923.07692 2556.56109)))
("SF_PLANTING" 0 ((6924.96256 6478.12964) (6916.58541 6496.98348) (6915.68982 6512.06629) (6934.38914 6534.69106)))
("SF_PLANTING" 0 ((7533.93665 6481.90045) (7458.52161 6481.75238) (7439.66844 6478.12964) (7383.10735 6478.27771)
(7368.02387 6481.89389) (6960.78405 6481.89389) (6924.96256 6478.12964)))
("SF_PLANTING" 0 ((6926.84740 6240.57308) (6926.84740 6217.94864)))
("SF_MASONRY_AND_ARCH" 0 ((6926.84740 3054.29864) (6927.00204 3031.68111) (6934.38914 3024.13247)))
("SF_PLANTING" 0 ((6926.84740 388.38518) (6934.53756 377.22828) (6949.47183 369.53337)))
("SF_PLANTING" 0 ((6926.84740 388.38518) (6930.77330 399.69253) (6949.47183 413.58360) (6968.32579 414.78224)))
("SF_SOLAR" 0 ((7096.53066 8144.79638) (7085.21844 8141.03213) (6957.01357 8141.03213) (6941.93088 8144.50023)
(6930.61867 8141.02557)))
("SF_PLANTING" 0 ((6949.47183 6689.29084) (6953.09536 6681.74299) (6952.03891 6662.90249) (6945.69446 6656.55848)
(6930.61867 6655.35419)))
("SF_PLANTING" 0 ((6953.24310 7096.53066) (6941.93088 7111.31097) (6934.38914 7111.61414)))
("SF_PLANTING" 0 ((6934.38914 7043.74084) (6928.04536 7039.81516) (6927.00204 7021.11640) (6941.93088 7006.03292)))
("SF_PLANTING" 0 ((6953.24310 6881.59853) (6934.38914 6881.59853)))
("SF_PLANTING" 0 ((6938.15962 6945.70136) (6938.01188 6896.68201) (6934.38914 6881.59853)))
("SF_PLANTING" 0 ((6934.38914 6534.69106) (6949.46561 6530.76538) (6964.55532 6512.06629)))
("SF_SOLAR" 0 ((6938.15962 7982.65452) (6938.15962 7993.96674)))
("SF_SOLAR" 0 ((6938.15962 7963.80090) (6938.15962 7952.48869)))
("SF_PLANTING" 0 ((6938.15962 6945.70136) (6960.78405 6945.70136)))
("SF_MASONRY_AND_ARCH" 0 ((6938.15962 2190.79966) (6964.55532 2194.27398) (7013.56776 2190.64502) (7021.11640
2183.25792)))
("SF_PLANTING" 0 ((6938.15962 316.74208) (6945.54672 305.42986) (6945.70136 286.57523)))
("SF_PLANTING" 0 ((6938.15962 316.74208) (6945.70136 326.84943) (6953.24310 328.05430)))
("SF_SOLAR" 0 ((6941.93088 8073.15226) (6949.47183 8084.46448)))
("SF_PLANTING" 0 ((6968.32579 7043.74084) (6955.95724 7013.58122) (6941.93088 7006.03292)))
("SF_PLANTING" 0 ((6987.93371 294.87161) (6968.32579 286.72364) (6945.70136 286.57523)))
("SF_PLANTING" 0 ((6949.47183 6689.29084) (6960.63631 6719.45701) (6958.89921 6738.31097)))
("SF_MASONRY_AND_ARCH" 0 ((6949.47183 1165.15837) (6950.67602 1134.99152) (6979.63801 1108.59729)))
("SF_MASONRY_AND_ARCH" 0 ((6949.47183 1165.15837) (7006.02670 1169.07658) (7013.57466 1172.70079)))
("SF_PLANTING" 0 ((6949.47183 531.67421) (6960.78405 521.41833) (7036.19910 481.45690) (7047.51131 471.34333)))
("SF_PLANTING" 0 ((6953.24310 328.05430) (6949.47183 369.53337)))
("SF_PLANTING" 0 ((6968.32579 377.07296) (6949.47183 369.53337)))
("SF_PLANTING" 0 ((6953.24310 6881.59853) (6957.01357 6862.74536)))
("SF_PLANTING" 0 ((6953.24310 6881.59853) (6982.21063 6907.99423) (6987.17975 6930.61867)))
("SF_PLANTING" 0 ((6953.24310 6772.24762) (6953.39423 6749.62319) (6958.89921 6738.31097)))
("SF_PLANTING" 0 ((6964.55532 6779.78857) (6953.24310 6772.24762)))
("SF_PLANTING" 0 ((6960.78405 6576.16867) (6953.24310 6602.56437)))
("SF_PLANTING" 0 ((6957.01357 6613.87658) (6953.24310 6602.56437)))
("SF_PLANTING" 0 ((6953.24310 6444.19299) (6972.09627 6398.94412)))
("SF_MASONRY_AND_ARCH" 0 ((6953.24310 2552.79061) (6972.09627 2552.79061)))
("SF_PLANTING" 0 ((6983.40848 328.05430) (6953.24310 328.05430)))
("SF_SOLAR" 0 ((6957.01357 8107.08891) (6979.63801 8114.48235) (6994.72070 8114.63054)))
("SF_PLANTING" 0 ((6968.32579 7043.74084) (6957.01357 7073.90622)))
("SF_PLANTING" 0 ((7028.65735 6862.74536) (7009.80419 6858.97410) (6957.01357 6862.74536)))
("SF_PLANTING" 0 ((6964.55532 6779.78857) (6958.21075 6813.72523) (6957.01357 6862.74536)))
("SF_MASONRY_AND_ARCH" 0 ((6964.55532 3340.87455) (6957.01357 3340.87455)))
("SF_PLANTING" 0 ((6983.40848 6742.08145) (6958.89921 6738.31097)))
("SF_SOLAR" 0 ((6960.78405 8133.48416) (6968.32579 8122.17195)))
("SF_SOLAR" 0 ((6960.78405 7952.48869) (6960.78405 7963.80090)))
("SF_PLANTING" 0 ((6960.78405 6945.70136) (6972.09627 6935.59333) (6987.17975 6930.61867)))
("SF_PLANTING" 0 ((6983.40848 6968.32579) (6972.09627 6960.77749) (6960.78405 6945.70136)))
("SF_MASONRY_AND_ARCH" 0 ((7055.05305 2631.97613) (7043.74084 2624.58903) (6983.40848 2620.81233) (6968.33269
2628.35339) (6960.78405 2639.51708)))
("SF_MASONRY_AND_ARCH" 0 ((6987.17975 2654.60057) (6968.33269 2653.39638) (6960.78405 2639.51708)))
("SF_SOLAR" 0 ((6968.32579 8050.52783) (6964.55532 8042.98643)))
("SF_PLANTING" 0 ((6964.55532 6779.78857) (6983.40848 6776.01810)))
("SF_MASONRY_AND_ARCH" 0 ((6964.55532 3525.64129) (6972.09627 3514.32885)))
("SF_MASONRY_AND_ARCH" 0 ((6972.09627 3536.95351) (6964.55532 3525.64129)))
("SF_SOLAR" 0 ((6968.32579 8012.82059) (6979.63801 8001.50837)))
("SF_PLANTING" 0 ((6998.49197 7039.96957) (6968.32579 7043.74084)))
("SF_PLANTING" 0 ((6968.32579 377.07296) (6971.80011 384.62229) (6968.32579 414.78224)))
("SF_PLANTING" 0 ((6968.32579 414.78224) (6983.40848 433.48699) (7006.03292 447.66176) (7024.87998 448.57048)
(7032.42862 444.94627)))
("SF_PLANTING" 0 ((6968.32579 377.07296) (6990.95373 368.47217) (7004.14808 356.33484)))
("SF_SOLAR" 0 ((6972.09627 8088.23529) (6979.63801 8088.23529) (6987.17975 8095.77670)))
("SF_MASONRY_AND_ARCH" 0 ((7319.00452 3514.32885) (7296.38009 3514.32885) (7273.75566 3514.32885) (7058.82353
3514.32885) (7036.19910 3514.32885) (7021.11640 3514.32885) (6972.09627 3514.32885)))
("SF_MASONRY_AND_ARCH" 0 ((6972.09627 3472.85068) (6968.48043 3487.93337) (6972.09627 3514.32885)))
("SF_MASONRY_AND_ARCH" 0 ((6972.09627 3472.85068) (6990.95023 3469.08643) (7311.46278 3469.08710) (7326.54627
3476.62115)))
("SF_MASONRY_AND_ARCH" 0 ((7032.42862 3092.00577) (7021.11640 3095.62930) (6979.64491 3095.92477) (6972.09627
3099.54751)))
("SF_MASONRY_AND_ARCH" 0 ((6987.17975 3016.59152) (6979.63801 3020.36199) (6972.09627 3012.82025)))
("SF_MASONRY_AND_ARCH" 0 ((6972.09627 1078.43043) (6968.48733 1089.74265) (6979.63801 1108.59729)))
("SF_SOLAR" 0 ((6975.86753 8103.31833) (6987.17975 8095.77670)))
("SF_PLANTING" 0 ((7039.96957 248.86878) (7021.11640 233.94005) (6990.95023 233.93450) (6975.86753 241.32636)))
("SF_PLANTING" 0 ((6987.93371 294.87161) (6975.86753 241.32636)))
("SF_SOLAR" 0 ((6979.63801 8122.17195) (6983.40848 8133.48416)))
("SF_SOLAR" 0 ((6987.17975 7982.65452) (6980.83597 7990.20271) (6979.63801 8001.50837)))
("SF_SOLAR" 0 ((6998.49197 8009.04977) (6987.18597 8007.85215) (6979.63801 8001.50837)))
("SF_MASONRY_AND_ARCH" 0 ((6979.63801 2582.95600) (7021.11640 2586.72104) (7036.19910 2583.10373) (7141.77952
2579.18552)))
("SF_MASONRY_AND_ARCH" 0 ((6979.63801 1923.07692) (6990.95023 1926.84118) (7088.98971 1926.84740)))
("SF_MASONRY_AND_ARCH" 0 ((7349.17070 1085.97285) (7334.08722 1089.73778) (7198.34061 1089.89106) (7130.46731
1104.67217) (7055.05305 1101.21018) (7024.88688 1112.07161) (6979.63801 1108.59729)))
("SF_SOLAR" 0 ((6987.17975 7926.09355) (6983.40848 7918.55204)))
("SF_PLANTING" 0 ((6983.40848 6968.32579) (7006.03292 6941.93088)))
("SF_PLANTING" 0 ((6983.40848 6968.32579) (6994.72760 6985.98201) (7013.57466 6990.95023)))
("SF_PLANTING" 0 ((7043.74084 6776.01810) (6983.40848 6776.01810)))
("SF_PLANTING" 0 ((6983.40848 6742.08145) (6983.40848 6776.01810)))
("SF_PLANTING" 0 ((6983.40848 6742.08145) (7021.11640 6726.99876)))
("SF_MASONRY_AND_ARCH" 0 ((6994.72070 3340.87455) (6983.40848 3340.87455)))
("SF_PLANTING" 0 ((6987.93371 294.87161) (6983.58597 305.31731) (6983.40848 328.05430)))
("SF_PLANTING" 0 ((6983.40848 328.05430) (6992.00939 346.90475) (7004.14808 356.33484)))
("SF_SOLAR" 0 ((7107.84287 8088.23529) (7006.03292 8088.38337) (6987.17975 8095.77670)))
("SF_SOLAR" 0 ((6987.17975 8058.06946) (7081.44796 8058.21742) (7092.76018 8061.69208) (7153.08552 8061.98812)
(7160.63348 8065.61086)))
("SF_PLANTING" 0 ((7006.03292 6941.93088) (6994.72760 6931.82296) (6987.17975 6930.61867)))
("SF_PLANTING" 0 ((6987.17975 6625.18880) (7021.11640 6598.79310)))
("SF_PLANTING" 0 ((6987.93371 294.87161) (7013.57466 276.45407) (7036.19910 267.72342)))
("SF_PLANTING" 0 ((6987.93371 294.87161) (7019.91844 324.28450) (7024.88688 346.90894)))
("SF_MASONRY_AND_ARCH" 0 ((6990.95023 1402.71493) (7043.74084 1410.40509) (7062.59400 1417.79695)))
("SF_PLANTING" 0 ((6994.72070 6685.52036) (6998.49197 6677.97862)))
("SF_MASONRY_AND_ARCH" 0 ((6994.72070 3129.71369) (7017.34514 3126.23869) (7028.65735 3129.71369)))
("SF_SOLAR" 0 ((6998.49197 8099.54751) (7013.57466 8107.08891)))
("SF_PLANTING" 0 ((6998.49197 7085.21844) (7006.03292 7077.67749)))
("SF_PLANTING" 0 ((6998.49197 7039.96957) (7013.57466 7017.34514)))
("SF_PLANTING" 0 ((6998.49197 7039.96957) (7006.03292 7077.67749)))
("SF_MASONRY_AND_ARCH" 0 ((7002.26244 1806.18495) (7024.88688 1802.41233)))
("SF_PLANTING" 0 ((7004.14808 356.33484) (7017.33552 353.25543) (7024.88688 346.90894)))
("SF_PLANTING" 0 ((7004.14808 356.33484) (7007.08314 384.61538) (7027.45950 422.32183) (7032.42862 444.94627)))
("SF_SOLAR" 0 ((7006.03292 8133.48416) (7007.08937 8118.40124) (7013.57466 8107.08891)))
("SF_SOLAR" 0 ((7006.03292 8069.38167) (7006.03292 8080.69389)))
("SF_PLANTING" 0 ((7036.19910 7081.44796) (7006.03292 7077.67749)))
("SF_PLANTING" 0 ((7036.19910 6941.93088) (7006.03292 6941.93088)))
("SF_MASONRY_AND_ARCH" 0 ((7043.74084 2111.61391) (7017.34514 2111.61391) (7006.03292 2104.07240)))
("SF_MASONRY_AND_ARCH" 0 ((7013.57466 1987.17975) (7009.80419 2021.11640)))
("SF_MASONRY_AND_ARCH" 0 ((7009.80419 2021.11640) (7013.42692 2036.19910) (7013.57466 2077.67749)))
("SF_SOLAR" 0 ((7043.74084 8103.31833) (7021.12262 8103.46629) (7013.57466 8107.08891)))
("SF_PLANTING" 0 ((7013.57466 7017.34514) (7013.57466 6990.95023)))
("SF_PLANTING" 0 ((7036.19910 7081.44796) (7039.82183 7073.89966) (7038.76550 7036.19910) (7013.57466 7017.34514)))
("SF_PLANTING" 0 ((7036.19910 6987.17975) (7013.57466 6990.95023)))
("SF_MASONRY_AND_ARCH" 0 ((7013.57466 1987.17975) (7168.17523 1987.17975)))
("SF_MASONRY_AND_ARCH" 0 ((7119.15509 1674.20814) (7017.34514 1674.20814)))
("SF_MASONRY_AND_ARCH" 0 ((7017.34514 1576.16799) (7017.35826 1595.02262) (7028.36120 1621.41686) (7017.49367
1647.81391) (7017.34514 1674.20814)))
("SF_PLANTING" 0 ((7073.90622 6515.83710) (7062.74864 6546.00328) (7061.38993 6587.47432) (7051.28179 6594.86776)
(7025.04152 6592.59740) (7021.11640 6598.79310)))
("SF_PLANTING" 0 ((7036.19910 6613.87658) (7021.11640 6598.79310)))
("SF_MASONRY_AND_ARCH" 0 ((7473.60509 2187.02839) (7447.20939 2190.79344) (7149.32127 2190.80588) (7134.23857
2194.27398) (7122.92636 2190.94740) (7039.96957 2190.65113) (7021.11640 2183.25792)))
("SF_MASONRY_AND_ARCH" 0 ((7311.46278 1240.57410) (7307.53767 1250.68767) (7292.60962 1255.50837) (7179.48744
1255.64989) (7156.86301 1251.89253) (7141.77952 1255.50837) (7055.05305 1255.66233) (7021.11640 1259.42590)))
("SF_MASONRY_AND_ARCH" 0 ((7024.88688 1206.63744) (7017.49977 1240.57410) (7021.11640 1259.42590)))
("SF_SOLAR" 0 ((7024.88688 8042.98643) (7085.21844 8042.83846) (7096.53066 8039.21561)))
("SF_SOLAR" 0 ((7190.79966 8009.04977) (7179.48744 8005.57511) (7160.63348 8009.04310) (7141.77952 8005.28552)
(7043.74084 8005.28552) (7024.88688 8012.82059)))
("SF_MASONRY_AND_ARCH" 0 ((7024.88688 2903.46912) (7024.88688 2911.01029)))
("SF_MASONRY_AND_ARCH" 0 ((7024.88688 2903.46912) (7171.94570 2903.46912) (7194.57014 2903.46912) (7213.42410
2903.46912)))
("SF_MASONRY_AND_ARCH" 0 ((7224.73631 2371.79514) (7217.18767 2375.41787) (7183.25792 2375.56561) (7160.63348
2371.80136) (7039.96957 2371.64661) (7028.81199 2366.96753) (7024.88688 2356.71165)))
("SF_MASONRY_AND_ARCH" 0 ((7024.88688 1802.41233) (7024.88688 1749.62387)))
("SF_MASONRY_AND_ARCH" 0 ((7024.88688 1802.41233) (7036.19910 1809.80011) (7228.50679 1809.96097) (7247.36075
1813.71968) (7273.75566 1810.25090) (7300.15057 1813.72455)))
("SF_MASONRY_AND_ARCH" 0 ((7126.69683 1738.31165) (7111.61414 1745.70351) (7024.88688 1749.62387)))
("SF_PLANTING" 0 ((7134.23857 478.88292) (7134.09005 501.50735) (7125.64050 520.36199) (7055.20079 595.77771)
(7024.88688 637.25396)))
("SF_PLANTING" 0 ((7066.36527 309.19966) (7051.27557 335.44830) (7024.88688 346.90894)))
("SF_SOLAR" 0 ((7028.65735 8069.38167) (7028.65735 8080.69389)))
("SF_SOLAR" 0 ((7028.65735 8024.13281) (7028.65735 8035.44502)))
("SF_PLANTING" 0 ((7028.65735 6862.74536) (7036.19910 6855.20362) (7043.74084 6855.20362)))
("SF_PLANTING" 0 ((7028.65735 6862.74536) (7046.32025 6896.68201) (7051.28179 6915.53518)))
("SF_MASONRY_AND_ARCH" 0 ((7028.65735 3171.19129) (7029.86154 3178.59152) (7047.51131 3193.81572)))
("SF_MASONRY_AND_ARCH" 0 ((7073.90622 1451.73360) (7039.96957 1456.70962) (7028.65735 1466.81844)))
("SF_MASONRY_AND_ARCH" 0 ((7055.05305 2631.97613) (7050.22545 2646.91041) (7032.42862 2654.60057)))
("SF_PLANTING" 0 ((7047.51131 471.34333) (7042.68439 452.63710) (7032.42862 444.94627)))
("SF_PLANTING" 0 ((7036.19910 7081.44796) (7036.19910 7100.30192)))
("SF_PLANTING" 0 ((7036.19910 6987.17975) (7036.19910 6957.01357)))
("SF_PLANTING" 0 ((7036.19910 6987.17975) (7062.59400 7008.59989) (7077.67749 7013.57466)))
("SF_PLANTING" 0 ((7107.84287 6919.30645) (7073.90000 6952.04536) (7058.82353 6956.86527) (7036.19910 6957.01357)))
("SF_PLANTING" 0 ((7036.19910 6941.93088) (7036.19910 6957.01357)))
("SF_PLANTING" 0 ((7036.19910 6941.93088) (7051.28179 6915.53518)))
("SF_MASONRY_AND_ARCH" 0 ((7051.28179 3337.10407) (7036.19910 3337.10407)))
("SF_MASONRY_AND_ARCH" 0 ((7036.19910 1327.29921) (7039.96957 1300.90498)))
("SF_MASONRY_AND_ARCH" 0 ((7036.19910 1327.29921) (7051.28179 1334.69321) (7160.63348 1334.84785) (7175.71618
1338.61143)))
("SF_PLANTING" 0 ((7043.74084 833.33428) (7036.19910 837.10407)))
("SF_PLANTING" 0 ((7036.19910 837.10407) (7039.82183 852.18609) (7039.96957 901.20758)))
("SF_PLANTING" 0 ((7039.96957 248.86878) (7036.19910 267.72342)))
("SF_PLANTING" 0 ((7066.36527 309.19966) (7048.56765 294.11765) (7036.19910 267.72342)))
("SF_PLANTING" 0 ((7043.74084 6776.01810) (7039.96957 6794.87206)))
("SF_MASONRY_AND_ARCH" 0 ((7141.77952 991.70532) (7047.50781 991.55962) (7036.56776 987.71312) (7036.34683 920.05939)
(7039.96957 901.20758)))
("SF_MASONRY_AND_ARCH" 0 ((7122.92636 904.97738) (7115.37771 901.35464) (7039.96957 901.20758)))
("SF_PLANTING" 0 ((7039.96957 248.86878) (7062.59400 248.86878)))
("SF_SOLAR" 0 ((7126.69683 8099.54751) (7104.07240 8106.94095) (7066.36527 8103.46652) (7047.51131 8110.85973)
(7043.74084 8118.40113) (7043.74084 8129.71335)))
("SF_PLANTING" 0 ((7107.84287 6843.89140) (7085.21844 6830.01301) (7062.59400 6832.73405) (7051.43032 6840.12749)
(7043.74084 6855.20362)))
("SF_PLANTING" 0 ((7107.84287 6874.05758) (7085.21844 6876.76550) (7055.05305 6865.31165) (7043.74084 6855.20362)))
("SF_PLANTING" 0 ((7043.74084 6776.01810) (7051.28179 6776.01810)))
("SF_PLANTING" 0 ((7051.28179 6655.35419) (7043.74084 6655.35419)))
("SF_MASONRY_AND_ARCH" 0 ((7043.74084 3212.66968) (7047.51131 3193.81572)))
("SF_ARCHITECTURE" 0 ((7579.18552 3797.13382) (7564.10283 3793.36391) (7062.59400 3793.37014) (7047.51131 3797.13382)))
("SF_ARCHITECTURE" 0 ((7100.30192 5705.12828) (7088.98971 5708.75068) (7062.59400 5707.69468) (7052.48597 5697.58665)
(7051.28201 3812.21719) (7047.51131 3797.13382)))
("SF_MASONRY_AND_ARCH" 0 ((7077.67749 3190.04525) (7047.51131 3193.81572)))
("SF_MASONRY_AND_ARCH" 0 ((7047.51131 1436.65158) (7062.59400 1417.79695)))
("SF_MASONRY_AND_ARCH" 0 ((7073.90622 1451.73360) (7062.59400 1441.62624) (7047.51131 1436.65158)))
("SF_PLANTING" 0 ((7130.46731 716.43948) (7047.51131 727.75170)))
("SF_PLANTING" 0 ((7077.67749 471.34333) (7047.51131 471.34333)))
("SF_SOLAR" 0 ((7051.28179 8190.04525) (7051.28179 8197.58665)))
("SF_SOLAR" 0 ((7051.28179 8069.38167) (7051.28179 8080.69389)))
("SF_SOLAR" 0 ((7051.28179 8020.36199) (7051.28179 8035.44502)))
("SF_SOLAR" 0 ((7247.36075 7941.17647) (7238.76267 7960.03009) (7224.73631 7971.18767) (7066.36527 7971.18778)
(7051.28179 7967.57172)))
("SF_PLANTING" 0 ((7051.28179 6915.53518) (7070.13575 6923.07692)))
("SF_PLANTING" 0 ((7062.59400 6738.31097) (7052.48597 6745.85882) (7051.28179 6776.01810)))
("SF_PLANTING" 0 ((7503.77048 6779.78857) (7454.75113 6776.02466) (7435.89717 6779.78201) (7141.77952 6779.79514)
(7092.76018 6783.55328) (7051.28179 6776.01810)))
("SF_PLANTING" 0 ((7066.36527 6644.04197) (7051.28179 6655.35419)))
("SF_PLANTING" 0 ((7051.28179 6655.35419) (7052.33824 6677.97862) (7058.96505 6688.08654) (7066.36527 6689.29084)))
("SF_ARCHITECTURE" 0 ((7051.28179 5765.45995) (7051.28179 5757.91855)))
("SF_MASONRY_AND_ARCH" 0 ((7051.28179 3046.75690) (7066.36527 3050.52195) (7171.94570 3050.52195) (7190.79966
3046.77002) (7213.42410 3050.52817)))
("SF_MASONRY_AND_ARCH" 0 ((7051.28179 2748.86878) (7051.28179 2722.47387)))
("SF_MASONRY_AND_ARCH" 0 ((7164.40396 2756.41052) (7104.07240 2756.26278) (7051.28179 2748.86878)))
("SF_MASONRY_AND_ARCH" 0 ((7055.05305 2631.97613) (7085.21844 2628.21799) (7134.23857 2631.82149) (7153.09174
2628.20486)))
("SF_MASONRY_AND_ARCH" 0 ((7055.05305 1625.18948) (7092.76018 1628.66312) (7104.07240 1625.48495) (7119.15509
1628.95305) (7220.96505 1628.95305) (7236.04853 1625.33654) (7303.92183 1625.04106) (7330.31674 1617.64706) (7413.27274
1621.56527) (7424.58495 1625.18948)))
("SF_MASONRY_AND_ARCH" 0 ((7058.82353 2111.61391) (7303.92183 2111.61391) (7311.46278 2111.61391) (7462.29287
2111.61391) (7477.37557 2111.61391) (7492.45826 2111.61391) (7624.42749 2111.61391) (7631.97681 2111.61391)))
("SF_PLANTING" 0 ((7058.82353 384.61538) (7066.22364 380.69027) (7092.76018 346.90894)))
("SF_SOLAR" 0 ((7062.59400 7888.38609) (7063.79819 7880.83801) (7073.90622 7869.68710) (7088.98971 7865.76165)))
("SF_MASONRY_AND_ARCH" 0 ((7469.83382 1421.56957) (7458.52161 1425.33314) (7379.33609 1425.33314) (7364.25339
1421.86505) (7326.54627 1425.33314) (7307.69231 1421.57443) (7190.79966 1423.98609) (7171.79796 1403.91980) (7164.40396
1402.72738) (7111.61414 1413.87941) (7062.59400 1417.79695)))
("SF_MASONRY_AND_ARCH" 0 ((7062.59400 1168.92817) (7085.21844 1165.31301) (7115.38462 1168.92817)))
("SF_PLANTING" 0 ((7111.61414 241.32636) (7104.06550 237.70430) (7073.90622 237.71120) (7062.59400 248.86878)))
("SF_PLANTING" 0 ((7085.21844 294.11765) (7082.34276 275.26301) (7062.59400 248.86878)))
("SF_SOLAR" 0 ((7073.90622 7911.01052) (7066.36527 7933.63495)))
("SF_SOLAR" 0 ((7247.36075 7941.17647) (7239.81210 7937.55385) (7088.98971 7937.39921) (7066.36527 7933.63495)))
("SF_PLANTING" 0 ((7085.21844 294.11765) (7066.36527 309.19966)))
("SF_SOLAR" 0 ((7070.13575 7978.88394) (7073.90622 7982.65452) (7073.90622 7993.96674)))
("SF_SOLAR" 0 ((7073.90622 8182.50385) (7077.67749 8178.73303) (7073.90622 8174.96222)))
("SF_SOLAR" 0 ((7073.90622 8118.40113) (7073.90622 8133.48416)))
("SF_SOLAR" 0 ((7073.90622 8069.38167) (7073.90622 8080.69389)))
("SF_SOLAR" 0 ((7073.90622 8035.44502) (7073.90622 8016.59118)))
("SF_PLANTING" 0 ((7107.84287 6919.30645) (7122.92636 6934.24084) (7152.02919 6953.39061) (7153.07862 6968.32579)
(7141.63179 6987.17975) (7119.15509 7009.65588) (7093.96437 7025.03518) (7088.83507 7043.73394) (7081.45419 7049.92964)
(7073.90622 7047.51131)))
("SF_ARCHITECTURE" 0 ((7560.33156 5795.62602) (7100.30192 5795.63258) (7085.21844 5799.24186) (7073.90622 5795.62602)))
("SF_MASONRY_AND_ARCH" 0 ((7073.90622 1451.73360) (7130.46731 1455.50622)))
("SF_MASONRY_AND_ARCH" 0 ((7277.52613 1549.77376) (7187.02839 1549.77998) (7164.40396 1553.54355) (7077.67749
1549.77376)))
("SF_PLANTING" 0 ((7077.67749 788.08541) (7119.15509 784.31278)))
("SF_PLANTING" 0 ((7096.53066 456.25848) (7077.67749 471.34333)))
("SF_PLANTING" 0 ((7164.40396 554.29864) (7160.47885 565.61086) (7088.98971 636.20520) (7021.11640 677.68360)
(6983.40848 692.76629) (6965.75939 693.44706) (6969.52376 667.42081) (7041.01912 542.98643) (7069.07941 505.27998)
(7076.62726 486.42534) (7077.67749 471.34333)))
("SF_MASONRY_AND_ARCH" 0 ((7175.71618 3344.64581) (7168.47760 3336.80792) (7088.99593 3337.25181) (7081.44796
3340.87455)))
("SF_PLANTING" 0 ((7085.21844 825.79186) (7119.15509 825.79186)))
("SF_PLANTING" 0 ((7085.21844 294.11765) (7104.07240 305.42986)))
("SF_SOLAR" 0 ((7092.76018 8163.65000) (7144.49434 8095.77670) (7160.63348 8065.61086)))
("SF_SOLAR" 0 ((7092.76018 8163.65000) (7115.38462 8174.65950) (7138.00905 8159.87941)))
("SF_SOLAR" 0 ((7096.53066 7948.71799) (7092.76018 7956.25939)))
("SF_PLANTING" 0 ((7092.76018 346.90894) (7092.91482 328.05430) (7104.07240 305.42986)))
("SF_PLANTING" 0 ((7168.17523 309.19966) (7160.62658 305.73224) (7145.55079 314.02104) (7111.61414 349.47387)
(7092.76018 346.90894)))
("SF_SOLAR" 0 ((7096.53066 8069.38167) (7096.53066 8080.69389)))
("SF_SOLAR" 0 ((7096.53066 8039.21561) (7145.55079 8039.21561)))
("SF_SOLAR" 0 ((7096.53066 8020.36199) (7096.53066 8039.21561)))
("SF_SOLAR" 0 ((7096.53066 7978.88394) (7096.53066 7993.96674)))
("SF_SOLAR" 0 ((7096.53066 7888.38609) (7096.67839 7858.22681) (7100.30192 7850.67873)))
("SF_PLANTING" 0 ((7096.53066 456.25848) (7122.92636 456.25848)))
("SF_PLANTING" 0 ((7168.17523 309.19966) (7167.12500 324.28450) (7159.72557 343.13631) (7101.49977 429.86425)
(7096.53066 456.25848)))
("SF_ARCHITECTURE" 0 ((7096.53088 4815.23337) (7134.23835 4815.23337)))
("SF_ARCHITECTURE" 0 ((7115.38462 4747.36007) (7096.53088 4766.21459) (7096.53088 4815.23337)))
("SF_ARCHITECTURE" 0 ((7100.30192 5705.12828) (7096.53088 4815.23337)))
("SF_ARCHITECTURE" 0 ((7100.30192 5705.12828) (7134.23835 5705.12828)))
("SF_SOLAR" 0 ((7104.07240 8193.81606) (7115.38462 8182.50385)))
("SF_PLANTING" 0 ((7160.63348 279.03563) (7141.77952 283.85486) (7111.62036 304.22500) (7104.07240 305.42986)))
("SF_PLANTING" 0 ((7107.84287 6919.30645) (7107.99140 6900.45249) (7115.38462 6881.59853)))
("SF_PLANTING" 0 ((7107.84287 6874.05758) (7107.84287 6843.89140)))
("SF_PLANTING" 0 ((7115.38462 6881.59853) (7107.84287 6874.05758)))
("SF_PLANTING" 0 ((7190.79966 6851.43314) (7164.40396 6828.96312) (7130.46731 6829.86471) (7107.84287 6843.89140)))
("SF_PLANTING" 0 ((7488.68778 6726.99876) (7300.15057 6727.00532) (7281.29740 6730.76267) (7262.44344 6727.14661)
(7187.02839 6727.00532) (7138.00905 6734.39186) (7107.84287 6734.53971)))
("SF_PLANTING" 0 ((7185.14355 254.52489) (7160.63348 233.94005) (7138.00905 233.93382) (7111.61414 241.32636)))
("SF_PLANTING" 0 ((7111.61414 241.32636) (7115.38462 267.72342)))
("SF_PLANTING" 0 ((7115.38462 6881.59853) (7130.46731 6877.97636) (7171.94570 6877.82805)))
("SF_ARCHITECTURE" 0 ((7115.38462 4747.36007) (7115.38462 4656.86233)))
("SF_ARCHITECTURE" 0 ((7115.38462 4747.36007) (7134.23835 4766.21459) (7134.23835 4815.23337)))
("SF_ARCHITECTURE" 1 ((7115.38462 4656.86233) (7126.54219 4649.31505) (7134.23835 4638.00905) (7134.23835 4415.53586)
(7117.27025 4394.79638) (7096.53088 4411.76471) (7096.53088 4638.00905) (7107.98450 4652.93744)))
("SF_MASONRY_AND_ARCH" 0 ((7209.65283 3190.04525) (7194.57014 3193.81572) (7130.46731 3193.66799) (7115.38462
3190.04525)))
("SF_SOLAR" 0 ((7119.15509 8069.38167) (7119.15509 8084.46448)))
("SF_SOLAR" 0 ((7119.15509 7978.88394) (7119.15509 7993.96674)))
("SF_SOLAR" 0 ((7119.15509 7911.01052) (7119.15509 7926.09355)))
("SF_SOLAR" 0 ((7122.92636 7948.71799) (7122.92636 7960.03020)))
("SF_PLANTING" 0 ((7156.86301 441.17647) (7122.92636 456.25848)))
("SF_PLANTING" 0 ((7134.23857 478.88292) (7122.92636 456.25848)))
("SF_MASONRY_AND_ARCH" 0 ((7126.69683 1738.31165) (7126.69683 1708.14480)))
("SF_MASONRY_AND_ARCH" 0 ((7126.69683 1738.31165) (7288.83835 1738.31652) (7334.08722 1742.08145)))
("SF_MASONRY_AND_ARCH" 0 ((7168.17523 1165.15837) (7126.69683 1168.92817)))
("SF_ARCHITECTURE" 0 ((7134.23835 5705.12828) (7134.23835 5656.10860) (7134.23835 4815.23337)))
("SF_ARCHITECTURE" 0 ((7175.71618 5705.12828) (7156.86301 5708.89887) (7134.23835 5705.12828)))
("SF_PLANTING" 0 ((7134.23857 478.88292) (7141.78643 477.67952) (7151.88767 467.57070) (7156.86301 441.17647)))
("SF_SOLAR" 0 ((7153.09174 8137.25498) (7139.21324 8152.33122) (7138.00905 8159.87941)))
("SF_SOLAR" 0 ((7356.71165 8103.31833) (7355.50758 8114.63054) (7326.39774 8156.10192) (7315.23405 8163.49536)
(7149.32127 8163.64344) (7138.00905 8159.87941)))
("SF_SOLAR" 0 ((7138.00905 7948.71799) (7138.00905 7960.03020)))
("SF_MASONRY_AND_ARCH" 0 ((7141.77952 2254.90170) (7138.00905 2273.75566)))
("SF_MASONRY_AND_ARCH" 0 ((7138.00905 2273.75566) (7156.86301 2277.37839) (7220.96505 2277.52613)))
("SF_SOLAR" 0 ((7141.77952 7993.96674) (7141.77952 7978.88394)))
("SF_SOLAR" 0 ((7141.77952 7926.09355) (7141.77952 7918.55204)))
("SF_PLANTING" 0 ((7149.32127 7070.13575) (7128.04943 7077.83156) (7131.66527 7092.76018) (7140.57545 7104.07240)
(7141.77952 7115.38462)))
("SF_SOLAR" 0 ((7145.55079 8020.36199) (7145.55079 8039.21561)))
("SF_SOLAR" 0 ((7164.40396 8042.98643) (7145.55079 8039.21561)))
("SF_MASONRY_AND_ARCH" 0 ((7205.88235 2552.79061) (7160.63348 2552.63597) (7145.55079 2541.47839)))
("SF_PLANTING" 0 ((7149.32127 7134.23857) (7156.86923 7140.58201) (7168.02670 7140.57523) (7180.54378 7111.61414)
(7191.69446 7096.53066) (7206.93179 7013.57466) (7217.19457 6994.72070)))
("SF_PLANTING" 0 ((7164.40396 7009.80419) (7163.34762 7021.11640) (7149.47590 7043.74084) (7149.32127 7070.13575)))
("SF_PLANTING" 0 ((7149.32127 7070.13575) (7157.00452 7080.24367) (7164.40396 7081.44796)))
("SF_SOLAR" 0 ((7311.46278 7911.01052) (7310.25871 7918.55860) (7278.57636 7956.25939) (7153.09174 8137.25498)))
("SF_SOLAR" 0 ((7322.77500 8141.02557) (7171.94570 8144.78982) (7153.09174 8137.25498)))
("SF_MASONRY_AND_ARCH" 0 ((7153.09174 2628.20486) (7153.09174 2620.66391)))
("SF_MASONRY_AND_ARCH" 0 ((7153.09174 2628.20486) (7213.42410 2631.97613)))
("SF_MASONRY_AND_ARCH" 0 ((7171.94570 1926.84740) (7156.86301 1926.84740)))
("SF_PLANTING" 0 ((7164.40396 554.29864) (7156.86301 535.44400)))
("SF_PLANTING" 0 ((7209.65283 343.13631) (7198.48914 350.68563) (7188.07862 365.76075) (7178.43100 395.92760)
(7156.86301 441.17647)))
("SF_SOLAR" 0 ((7224.73631 7982.65452) (7160.63348 8065.61086)))
("SF_PLANTING" 0 ((7185.14355 254.52489) (7160.63348 279.03563)))
("SF_PLANTING" 0 ((7160.63348 279.03563) (7171.94570 301.66007)))
("SF_SOLAR" 0 ((7164.40396 7978.88394) (7164.40396 7993.96674)))
("SF_SOLAR" 0 ((7164.40396 7960.03020) (7164.40396 7952.48869)))
("SF_MASONRY_AND_ARCH" 0 ((7164.40396 2771.49321) (7164.40396 2756.41052)))
("SF_MASONRY_AND_ARCH" 0 ((7175.71618 2748.86878) (7164.40396 2756.41052)))
("SF_MASONRY_AND_ARCH" 0 ((7190.79966 991.70532) (7164.40396 991.70532)))
("SF_PLANTING" 0 ((7164.40396 554.29864) (7213.42410 546.75622)))
("SF_MASONRY_AND_ARCH" 0 ((7179.48744 1975.86753) (7168.17523 1987.17975)))
("SF_MASONRY_AND_ARCH" 0 ((7168.17523 1987.17975) (7168.54321 2006.71437) (7179.48744 2009.80419)))
("SF_PLANTING" 0 ((7168.17523 309.19966) (7171.94570 301.66007)))
("SF_PLANTING" 0 ((7190.79966 6858.97410) (7171.94570 6877.82805)))
("SF_PLANTING" 0 ((7183.25792 6923.07692) (7182.20158 6907.99423) (7171.94570 6877.82805)))
("SF_MASONRY_AND_ARCH" 0 ((7171.94570 1926.84740) (7175.86471 1885.36980) (7183.40633 1871.49050) (7217.19457
1866.66357) (7315.23405 1866.36810) (7326.54627 1862.74536)))
("SF_MASONRY_AND_ARCH" 0 ((7175.71618 1934.38914) (7171.94570 1926.84740)))
("SF_PLANTING" 0 ((7185.14355 254.52489) (7185.97896 282.80543) (7182.05995 294.11075) (7171.94570 301.66007)))
("SF_ARCHITECTURE" 0 ((7175.71618 5705.12828) (7205.88235 5705.12828)))
("SF_ARCHITECTURE" 0 ((7175.71618 5705.12828) (7175.71640 5520.36199) (7175.71640 5501.50871) (7175.71640 5429.86425)
(7175.71640 5411.01097) (7175.71640 5324.28314) (7175.71640 5305.42986) (7175.71640 5275.26437) (7175.71640 5011.31222)
(7175.71640 4988.68778) (7175.71640 4932.12670) (7175.71640 4913.27342) (7175.71640 4343.89140) (7175.71640 4325.03812)
(7175.71640 4215.68586) (7175.71640 4162.89593) (7175.71640 4144.04265) (7175.71640 3910.25600) (7175.71640 3895.17387)
(7175.71640 3846.16007) (7175.71640 3839.81663) (7187.02839 3838.61900) (7198.18597 3839.81663) (7202.10498 3849.92500)
(7202.11810 5414.78088) (7209.65305 5433.63541) (7205.88235 5705.12828)))
("SF_MASONRY_AND_ARCH" 0 ((7175.71618 3367.27025) (7172.24186 3374.81810) (7179.48744 3404.97738)))
("SF_MASONRY_AND_ARCH" 0 ((7175.71618 3288.08473) (7171.95882 3276.77251) (7175.71618 3257.91855)))
("SF_MASONRY_AND_ARCH" 0 ((7175.71618 3257.91855) (7183.26482 3254.29581) (7213.42410 3254.14808)))
("SF_MASONRY_AND_ARCH" 0 ((7175.71618 2748.86878) (7213.42410 2748.86878)))
("SF_MASONRY_AND_ARCH" 0 ((7175.71618 2748.86878) (7179.48744 2722.47387)))
("SF_MASONRY_AND_ARCH" 0 ((7175.71618 1338.61143) (7175.71618 1376.32070)))
("SF_MASONRY_AND_ARCH" 0 ((7688.53790 1331.07093) (7639.51640 1331.07093) (7616.89197 1338.61143) (7594.26753
1331.07093) (7458.52161 1334.84785) (7439.66844 1338.59898) (7420.81448 1334.84785) (7198.34061 1334.84785) (7175.71618
1338.61143)))
("SF_SOLAR" 0 ((7179.48744 8061.84005) (7194.57014 8058.06946)))
("SF_PLANTING" 0 ((7179.48744 874.81052) (7179.48744 867.27093)))
("SF_PLANTING" 0 ((7179.48744 867.27093) (7190.79966 866.06606) (7202.10498 855.95871) (7231.07941 814.47964)
(7265.16448 720.21210) (7277.37839 663.65102) (7277.67387 625.94932) (7281.29740 618.40215)))
("SF_PLANTING" 0 ((7179.48744 867.27093) (7175.86391 859.72161) (7175.87081 776.77319) (7187.02839 761.68835)))
("SF_PLANTING" 0 ((7202.11188 6960.78405) (7188.22636 6949.47183) (7183.25792 6923.07692)))
("SF_PLANTING" 0 ((7217.19457 6934.38914) (7213.26946 6928.03857) (7202.11188 6924.12636) (7183.25792 6923.07692)))
("SF_MASONRY_AND_ARCH" 0 ((7190.79966 1470.58824) (7183.25792 1466.81844)))
("SF_MASONRY_AND_ARCH" 0 ((7183.25792 1165.15837) (7190.80588 1161.68405) (7220.96505 1165.15837)))
("SF_PLANTING" 0 ((7185.14355 254.52489) (7232.27726 252.79389) (7247.36075 260.18100)))
("SF_SOLAR" 0 ((7187.02839 8133.48416) (7190.79966 8125.94276)))
("SF_SOLAR" 0 ((7187.02839 7993.96674) (7187.02839 7982.65452)))
("SF_SOLAR" 0 ((7187.02839 7963.80090) (7187.02839 7948.71799)))
("SF_PLANTING" 0 ((7190.79966 727.75170) (7184.45588 754.14118) (7187.02839 761.68835)))
("SF_PLANTING" 0 ((7194.57014 765.46097) (7187.02839 761.68835)))
("SF_SOLAR" 0 ((7356.71165 8103.31833) (7258.67296 8099.39955) (7247.36075 8095.93133) (7190.79966 8103.31833)))
("SF_PLANTING" 0 ((7190.79966 6851.43314) (7190.79966 6858.97410)))
("SF_PLANTING" 0 ((7190.79966 6858.97410) (7224.73631 6884.17206) (7247.36075 6890.18971) (7262.44344 6900.45249)))
("SF_PLANTING" 0 ((7190.79966 6851.43314) (7228.50679 6832.72749) (7292.60962 6832.73405) (7303.91493 6840.12749)
(7319.00452 6858.97410)))
("SF_MASONRY_AND_ARCH" 0 ((7190.79966 991.70532) (7194.57014 953.99604) (7190.79966 938.91403)))
("SF_MASONRY_AND_ARCH" 0 ((7190.79966 991.70532) (7209.65283 1002.86222) (7349.17070 1006.93507) (7375.56561
1018.09955)))
("SF_PLANTING" 0 ((7190.79966 727.75170) (7194.57014 693.81505)))
("SF_PLANTING" 0 ((7202.11188 735.29412) (7190.79966 727.75170)))
("SF_PLANTING" 0 ((7213.42410 690.04525) (7194.57014 693.81505)))
("SF_PLANTING" 0 ((7213.42410 580.69287) (7203.16131 599.54751) (7198.48835 625.94174) (7194.57014 693.81505)))
("SF_PLANTING" 0 ((7202.11188 6960.78405) (7217.19457 6934.38914)))
("SF_PLANTING" 0 ((7217.19457 6987.17975) (7202.11188 6960.78405)))
("SF_ARCHITECTURE" 0 ((7205.88235 5705.12828) (7224.73631 5708.89887) (7247.36075 5705.12828)))
("SF_SOLAR" 0 ((7209.65283 8133.48416) (7209.65283 8118.40113)))
("SF_SOLAR" 0 ((7209.65283 7960.03020) (7209.65283 7952.48869)))
("SF_PLANTING" 0 ((7209.65283 343.13631) (7228.50679 343.13631)))
("SF_PLANTING" 0 ((7209.65283 343.13631) (7210.85701 298.03586) (7247.36075 267.72342)))
("SF_MASONRY_AND_ARCH" 0 ((7228.50679 2013.57466) (7213.42410 2013.57466)))
("SF_PLANTING" 0 ((7213.42410 580.69287) (7213.42410 546.75622)))
("SF_PLANTING" 0 ((7213.42410 580.69287) (7227.30260 595.77771) (7232.27726 629.71437)))
("SF_PLANTING" 0 ((7224.73631 501.50735) (7213.42410 546.75622)))
("SF_SOLAR" 0 ((7217.19457 8061.84005) (7379.33609 8061.83348) (7394.41957 8058.06946)))
("SF_SOLAR" 0 ((7228.50679 8009.04977) (7217.19457 8005.27896)))
("SF_PLANTING" 0 ((7217.19457 6987.17975) (7217.19457 6994.72070)))
("SF_PLANTING" 0 ((7243.58948 7013.57466) (7217.19457 6994.72070)))
("SF_PLANTING" 0 ((7217.19457 6987.17975) (7239.81900 6979.78631) (7258.67296 6979.63801)))
("SF_PLANTING" 0 ((7217.19457 6934.38914) (7251.13122 6934.38914)))
("SF_MASONRY_AND_ARCH" 0 ((7492.45826 2269.98518) (7481.14604 2262.59808) (7424.58495 2259.87081) (7360.48292
2262.43722) (7345.39943 2258.96912) (7330.31674 2262.43032) (7311.46278 2258.68609) (7296.38009 2262.29570) (7243.58948
2262.59118) (7228.51369 2267.41188) (7220.96505 2277.52613)))
("SF_MASONRY_AND_ARCH" 0 ((7228.50679 2330.31674) (7220.96505 2277.52613)))
("SF_MASONRY_AND_ARCH" 0 ((7228.50679 2330.31674) (7224.88405 2337.86471) (7224.73631 2371.79514)))
("SF_MASONRY_AND_ARCH" 0 ((7224.73631 2371.79514) (7239.81900 2379.18767) (7288.83835 2379.33609)))
("SF_PLANTING" 0 ((7224.73631 501.50735) (7220.97817 478.88292) (7224.58857 463.80090) (7223.06471 429.86425)
(7230.17839 395.92760) (7228.50679 343.13631)))
("SF_PLANTING" 0 ((7224.73631 501.50735) (7247.36075 510.10611) (7266.21391 526.70577) (7281.29740 531.67421)))
("SF_MASONRY_AND_ARCH" 0 ((7228.50679 2330.31674) (7303.92183 2330.31052) (7375.56561 2324.87466) (7450.98066
2330.02059) (7466.06335 2326.54627)))
("SF_MASONRY_AND_ARCH" 0 ((7262.44344 1463.04581) (7228.50679 1470.58824)))
("SF_PLANTING" 0 ((7228.50679 343.13631) (7243.58948 328.05430)))
("SF_SOLAR" 0 ((7232.27726 8137.25498) (7232.27726 8122.17195)))
("SF_SOLAR" 0 ((7232.27726 8084.46448) (7232.27726 8069.38167)))
("SF_SOLAR" 0 ((7232.27726 7918.55204) (7232.27726 7926.09355)))
("SF_MASONRY_AND_ARCH" 0 ((7273.75566 912.51980) (7232.27726 916.28959)))
("SF_SOLAR" 0 ((7394.41957 8039.21561) (7236.04853 8039.21561)))
("SF_SOLAR" 0 ((7236.04853 7986.42534) (7239.81900 7993.96674)))
("SF_SOLAR" 0 ((7251.13122 8114.63054) (7239.81900 8114.63054)))
("SF_SOLAR" 0 ((7243.58948 7971.34231) (7251.13122 7975.11312)))
("SF_PLANTING" 0 ((7243.58948 7013.57466) (7262.44344 7013.57466)))
("SF_PLANTING" 0 ((7273.75566 7066.36527) (7254.90170 7065.16097) (7244.79367 7055.05271) (7243.58948 7013.57466)))
("SF_PLANTING" 0 ((7243.58948 328.05430) (7250.98281 282.80543) (7247.36075 267.72342)))
("SF_PLANTING" 0 ((7281.29740 403.47002) (7259.87081 361.99095) (7253.70385 339.36652) (7243.58948 328.05430)))
("SF_SOLAR" 0 ((7247.36075 7941.17647) (7269.98518 7914.78133)))
("SF_ARCHITECTURE" 0 ((7247.36075 5705.12828) (7277.52613 5705.12828)))
("SF_ARCHITECTURE" 0 ((7247.36075 5705.12828) (7247.36052 5331.82545) (7247.36052 5309.20102) (7247.36052 5260.18100)
(7247.36052 5245.09762) (7247.36052 5184.76663) (7247.36052 4370.28699) (7247.36052 4347.66256) (7247.36052 4144.04265)
(7247.36052 4125.18812) (7247.36052 3955.50486) (7247.36052 3936.65158) (7247.36052 3842.38959) (7255.05633 3836.04615)
(7262.44344 3834.84785) (7273.60102 3836.04615) (7277.52636 3846.15385) (7277.53235 5633.48416) (7281.29740 5656.10860)
(7281.14966 5693.81572) (7277.52613 5705.12828)))
("SF_PLANTING" 0 ((7247.36075 260.18100) (7247.36075 267.72342)))
("SF_PLANTING" 0 ((7247.36075 260.18100) (7277.52613 256.41120)))
("SF_SOLAR" 0 ((7251.13122 7846.90803) (7251.13122 7854.44943)))
("SF_PLANTING" 0 ((7251.13122 6934.38914) (7262.44344 6900.45249)))
("SF_PLANTING" 0 ((7251.13122 6934.38914) (7262.44344 6968.32579)))
("SF_MASONRY_AND_ARCH" 0 ((7258.67296 1168.92817) (7251.13122 1165.15837)))
("SF_SOLAR" 0 ((7254.90170 8069.38167) (7254.90170 8084.46448)))
("SF_MASONRY_AND_ARCH" 0 ((7273.75566 886.12274) (7254.90170 893.66516)))
("SF_SOLAR" 0 ((7258.67296 8133.48416) (7262.44344 8122.17195)))
("SF_SOLAR" 0 ((7258.67296 8005.27896) (7428.35622 8005.27896)))
("SF_PLANTING" 0 ((7258.67296 6979.63801) (7262.44344 6968.32579)))
("SF_PLANTING" 0 ((7258.67296 6979.63801) (7262.29570 6987.18631) (7262.44344 7013.57466)))
("SF_MASONRY_AND_ARCH" 0 ((7258.67296 1168.92817) (7266.21391 1165.15837)))
("SF_MASONRY_AND_ARCH" 0 ((7266.21391 1187.78281) (7259.87081 1180.23552) (7258.67296 1168.92817)))
("SF_PLANTING" 0 ((7285.06787 7047.51131) (7280.24095 7025.03518) (7262.44344 7013.57466)))
("SF_PLANTING" 0 ((7337.85848 7006.03292) (7307.69231 6999.38654) (7288.69061 6977.06505) (7262.44344 6968.32579)))
("SF_PLANTING" 0 ((7296.38009 6892.91075) (7277.52613 6900.30419) (7262.44344 6900.45249)))
("SF_MASONRY_AND_ARCH" 0 ((7277.52613 2013.57466) (7269.98518 2009.80419)))
("SF_SOLAR" 0 ((7273.75566 8031.67421) (7273.75566 8020.36199)))
("SF_PLANTING" 0 ((7273.75566 7066.36527) (7285.06787 7047.51131)))
("SF_ARCHITECTURE" 0 ((7273.75566 7066.36527) (7277.51991 7081.44796) (7277.52613 7541.47817)))
("SF_MASONRY_AND_ARCH" 0 ((7345.39943 904.97738) (7322.77500 912.37138) (7273.75566 912.51980)))
("SF_MASONRY_AND_ARCH" 0 ((7273.75566 912.51980) (7273.75566 886.12274)))
("SF_MASONRY_AND_ARCH" 0 ((7345.39943 882.35294) (7311.46278 878.87862) (7273.75566 886.12274)))
("SF_SOLAR" 0 ((7277.52613 8088.23529) (7277.52613 8073.15226)))
("SF_ARCHITECTURE" 0 ((7337.85848 5693.81606) (7322.77523 5704.07195) (7307.69231 5710.57036) (7277.52613 5705.12828)))
("SF_PLANTING" 0 ((7330.31674 241.32636) (7288.83835 242.53122) (7277.52613 256.41120)))
("SF_PLANTING" 0 ((7311.46278 279.03563) (7296.38009 274.05962) (7277.52613 256.41120)))
("SF_SOLAR" 0 ((7281.29740 7967.57172) (7296.38009 7971.33575) (7443.43891 7971.18767) (7450.83213 7967.41697)
(7462.29287 7948.71799)))
("SF_PLANTING" 0 ((7281.29740 531.67421) (7286.27206 493.96776) (7300.15057 482.65554)))
("SF_PLANTING" 0 ((7303.92183 576.92308) (7297.57726 572.99796) (7287.64740 539.22149) (7281.29740 531.67421)))
("SF_PLANTING" 0 ((7300.15057 467.57070) (7293.65905 456.25848) (7281.29740 403.47002)))
("SF_PLANTING" 0 ((7281.29740 403.47002) (7322.77500 407.08518) (7334.08722 399.69740)))
("SF_SOLAR" 0 ((7285.06787 7846.90803) (7288.83835 7861.99095) (7285.06787 7888.38609)))
("SF_ARCHITECTURE" 0 ((7285.06787 7688.53699) (7285.06787 7718.70283)))
("SF_PLANTING" 0 ((7285.06787 7047.51131) (7292.46109 7051.43665) (7307.69853 7076.47319) (7337.85848 7077.67749)))
("SF_MASONRY_AND_ARCH" 0 ((7285.06787 3337.10407) (7285.06165 3039.21595) (7281.29740 3016.59152) (7285.06165
2990.19581) (7285.06787 2594.26821)))
("SF_MASONRY_AND_ARCH" 0 ((7401.96075 3114.63020) (7401.96075 3378.57557) (7390.64830 3385.96878) (7277.53303
3384.91934) (7270.13982 3374.81120) (7270.13360 3355.95803) (7277.66776 3341.02919) (7285.06787 3337.10407)))
("SF_MASONRY_AND_ARCH" 0 ((7368.02410 3110.85973) (7368.02410 3348.41007) (7349.17070 3359.58009) (7319.00452
3359.58009) (7285.06787 3337.10407)))
("SF_MASONRY_AND_ARCH" 0 ((7330.31674 2564.10283) (7300.15057 2580.24186) (7285.06787 2594.26821)))
("SF_MASONRY_AND_ARCH" 0 ((7330.31674 2549.01934) (7288.83835 2545.25577) (7277.68077 2549.17398) (7273.91029
2556.56109) (7273.91029 2582.95600) (7285.06787 2594.26821)))
("SF_PLANTING" 0 ((7288.83835 825.79186) (7303.92183 822.02206) (7352.94118 825.79186)))
("SF_MASONRY_AND_ARCH" 0 ((7292.60962 1191.55260) (7303.91493 1192.75747) (7311.46278 1202.86482)))
("SF_SOLAR" 0 ((7296.38009 7839.36652) (7303.77410 7812.97138) (7303.92183 7779.03473)))
("SF_SOLAR" 0 ((7303.92183 7858.22025) (7296.38009 7839.36652)))
("SF_PLANTING" 0 ((7296.38009 6892.91075) (7319.00452 6885.36980)))
("SF_PLANTING" 0 ((7296.38009 6892.91075) (7300.15057 6919.30645)))
("SF_MASONRY_AND_ARCH" 0 ((7307.69231 1549.77376) (7296.38009 1549.77376)))
("SF_SOLAR" 0 ((7300.15057 8133.48416) (7300.15057 8114.63054)))
("SF_SOLAR" 0 ((7300.15057 8069.38167) (7300.15057 8084.46448)))
("SF_SOLAR" 0 ((7300.15057 8031.67421) (7300.15057 8016.59118)))
("SF_SOLAR" 0 ((7300.15057 7978.88394) (7300.15057 7990.19615)))
("SF_SOLAR" 0 ((7303.92183 7858.22025) (7300.15057 7865.76165)))
("SF_MASONRY_AND_ARCH" 0 ((7300.15057 1463.04581) (7307.69231 1459.27602)))
("SF_PLANTING" 0 ((7300.15057 467.57070) (7300.15057 482.65554)))
("SF_PLANTING" 0 ((7341.62896 599.54751) (7340.57262 584.46550) (7321.71867 520.36199) (7310.26493 493.96776)
(7300.15057 482.65554)))
("SF_PLANTING" 0 ((7360.48292 493.96776) (7322.77500 472.39208) (7300.15057 467.57070)))
("SF_SOLAR" 0 ((7303.92183 7858.22025) (7356.71165 7861.98439) (7518.85396 7861.99751) (7549.01934 7865.76165)))
("SF_ARCHITECTURE" 0 ((7303.92183 7779.03473) (7311.46968 7775.41199) (7337.85848 7775.26391)))
("SF_PLANTING" 0 ((7311.46278 339.36652) (7303.92183 335.59672)))
("SF_ARCHITECTURE" 0 ((7341.62896 7631.97590) (7307.69231 7631.97590)))
("SF_ARCHITECTURE" 0 ((7315.23405 7582.95622) (7307.84072 7601.80995) (7307.69231 7631.97590)))
("SF_MASONRY_AND_ARCH" 0 ((7307.69231 2383.10735) (7321.57093 2394.41957) (7322.77500 2420.81448)))
("SF_MASONRY_AND_ARCH" 0 ((7567.87330 1542.23133) (7556.56109 1538.46776) (7319.00452 1539.66640) (7307.69231
1549.77376)))
("SF_MASONRY_AND_ARCH" 0 ((7311.46278 1583.71041) (7311.46278 1576.16799) (7311.46278 1568.62839) (7307.69231
1549.77376)))
("SF_SOLAR" 0 ((7492.45826 7941.17647) (7484.91041 7937.55385) (7326.54627 7937.39921) (7311.46278 7933.63495)))
("SF_PLANTING" 0 ((7334.08722 6941.93088) (7311.46278 6938.15962)))
("SF_MASONRY_AND_ARCH" 0 ((7311.46278 1312.21719) (7311.46278 1297.13518)))
("SF_MASONRY_AND_ARCH" 0 ((7375.56561 1161.38857) (7364.25339 1165.01063) (7311.46278 1165.15837)))
("SF_PLANTING" 0 ((7311.46278 339.36652) (7315.23405 320.51188)))
("SF_PLANTING" 0 ((7311.46278 339.36652) (7334.08722 399.69740)))
("SF_PLANTING" 0 ((7311.46278 279.03563) (7330.31674 267.72342)))
("SF_PLANTING" 0 ((7311.46278 279.03563) (7315.23405 320.51188)))
("SF_ARCHITECTURE" 0 ((7334.08744 7579.18552) (7315.23405 7582.95622)))
("SF_MASONRY_AND_ARCH" 0 ((7315.23405 2496.22952) (7330.31674 2496.22952)))
("SF_MASONRY_AND_ARCH" 0 ((7330.31674 1813.72455) (7315.23405 1809.95475)))
("SF_PLANTING" 0 ((7371.79514 361.99095) (7337.85158 325.34016) (7315.23405 320.51188)))
("SF_PLANTING" 0 ((7319.00452 6885.36980) (7319.00452 6858.97410)))
("SF_PLANTING" 0 ((7337.85848 6904.22296) (7319.00452 6885.36980)))
("SF_PLANTING" 0 ((7386.87783 6855.20362) (7334.08722 6851.58100) (7319.00452 6858.97410)))
("SF_MASONRY_AND_ARCH" 0 ((7326.54627 3476.62115) (7319.00452 3514.32885)))
("SF_MASONRY_AND_ARCH" 0 ((7322.77500 3536.95351) (7319.00452 3514.32885)))
("SF_MASONRY_AND_ARCH" 0 ((7319.00452 1972.09627) (7326.55249 1975.71980) (7368.02387 1975.86753)))
("SF_SOLAR" 0 ((7322.77500 8171.19163) (7322.77500 8178.73303)))
("SF_SOLAR" 0 ((7322.77500 8088.23529) (7322.77500 8069.38167)))
("SF_SOLAR" 0 ((7322.77500 8027.90339) (7322.77500 8016.59118)))
("SF_SOLAR" 0 ((7322.77500 7993.96674) (7322.77500 7978.88394)))
("SF_SOLAR" 0 ((7322.77500 7948.71799) (7322.77500 7960.03020)))
("SF_MASONRY_AND_ARCH" 0 ((7322.77500 2420.81448) (7322.77500 2458.52161)))
("SF_MASONRY_AND_ARCH" 0 ((7322.77500 2420.81448) (7424.58495 2420.80826) (7454.75113 2417.04400)))
("SF_ARCHITECTURE" 0 ((7337.85848 3846.15385) (7322.77523 3831.07048)))
("SF_MASONRY_AND_ARCH" 0 ((7326.54627 3476.62115) (7337.85848 3480.37930) (7394.41957 3476.62115) (7417.04400
3480.38620) (7631.97681 3479.04672) (7650.82862 3469.22862) (7767.72342 3469.08643) (7801.66007 3472.85068) (7831.82410
3469.08643) (7850.67873 3472.83756) (7865.76075 3469.08020)))
("SF_MASONRY_AND_ARCH" 0 ((7371.79514 2009.80419) (7326.54627 2013.57466)))
("SF_MASONRY_AND_ARCH" 0 ((7326.54627 1862.74536) (7330.31674 1813.72455)))
("SF_MASONRY_AND_ARCH" 0 ((7417.04400 1866.51584) (7341.62896 1866.36810) (7326.54627 1862.74536)))
("SF_MASONRY_AND_ARCH" 0 ((7330.31674 2549.01934) (7330.31674 2564.10283)))
("SF_MASONRY_AND_ARCH" 0 ((7368.02410 2575.41505) (7345.39943 2574.21086) (7330.31674 2564.10283)))
("SF_MASONRY_AND_ARCH" 0 ((7330.31674 2549.01934) (7349.17070 2545.24887) (7368.02410 2549.01934)))
("SF_MASONRY_AND_ARCH" 0 ((7492.45826 1809.95475) (7345.39943 1809.96097) (7330.31674 1813.72455)))
("SF_PLANTING" 0 ((7330.31674 241.32636) (7330.31674 267.72342)))
("SF_PLANTING" 0 ((7386.87783 312.97229) (7371.94287 308.14400) (7330.31674 267.72342)))
("SF_PLANTING" 0 ((7330.31674 241.32636) (7345.39943 233.93450) (7394.41957 233.93382) (7413.26652 238.75373)
(7420.81448 245.09898)))
("SF_PLANTING" 0 ((7334.08722 6941.93088) (7337.85848 6904.22296)))
("SF_PLANTING" 0 ((7334.08722 6941.93088) (7340.43100 6979.63801) (7337.85848 7006.03292)))
("SF_MASONRY_AND_ARCH" 0 ((7334.08722 1768.47568) (7334.08722 1742.08145)))
("SF_MASONRY_AND_ARCH" 0 ((7496.22952 1742.08145) (7454.75113 1741.93371) (7428.35622 1736.64005) (7368.02387
1741.92681) (7349.17070 1738.46493) (7334.08722 1742.08145)))
("SF_PLANTING" 0 ((7341.62896 599.54751) (7334.08722 610.85973)))
("SF_PLANTING" 0 ((7334.08722 399.69740) (7349.17070 399.69740)))
("SF_ARCHITECTURE" 0 ((7334.08744 7579.18552) (7337.85848 7096.53066)))
("SF_ARCHITECTURE" 0 ((7334.08744 7579.18552) (7360.48292 7586.72048) (7383.10735 7582.96278) (7628.20419 7582.95622)
(7673.45305 7586.57896) (7692.30769 7579.18552)))
("SF_ARCHITECTURE" 0 ((7696.07749 7767.72251) (7677.22568 7775.25735) (7337.85848 7775.26391)))
("SF_ARCHITECTURE" 0 ((7341.62896 7631.97590) (7341.62274 7756.41029) (7337.85848 7775.26391)))
("SF_PLANTING" 0 ((7337.85848 7096.53066) (7337.85848 7077.67749)))
("SF_PLANTING" 0 ((7409.50226 7138.00905) (7368.02387 7101.50622) (7337.85848 7096.53066)))
("SF_PLANTING" 0 ((7337.85848 7006.03292) (7337.85848 7077.67749)))
("SF_PLANTING" 0 ((7337.85848 7006.03292) (7352.94118 7006.03292)))
("SF_PLANTING" 0 ((7337.85848 6904.22296) (7368.02387 6904.22296)))
("SF_ARCHITECTURE" 0 ((7337.85848 3846.15385) (7337.86471 4966.06335) (7341.62896 4988.68778) (7337.86471 5015.08337)
(7337.85848 5693.81606)))
("SF_ARCHITECTURE" 0 ((7337.85848 5693.81606) (7364.25339 5708.75068) (7398.19005 5705.12828)))
("SF_ARCHITECTURE" 0 ((7356.71188 3834.84163) (7337.85848 3846.15385)))
("SF_SOLAR" 0 ((7345.39943 8073.15226) (7341.62896 8088.23529)))
("SF_ARCHITECTURE" 0 ((7341.62896 7631.97590) (7386.87783 7631.97590) (7401.96052 7631.97590) (7477.37557 7631.97590)
(7492.45826 7631.97590) (7522.62443 7631.97590) (7545.24887 7631.97590) (7564.10283 7631.97590) (7635.74661 7631.97590)
(7692.30769 7639.51731)))
("SF_PLANTING" 0 ((7341.62896 599.54751) (7351.73699 607.09480) (7352.94118 622.17195)))
("SF_SOLAR" 0 ((7345.39943 8020.36199) (7345.39943 8027.90339)))
("SF_SOLAR" 0 ((7345.39943 7948.71799) (7345.39943 7960.03020)))
("SF_SOLAR" 0 ((7345.39943 7926.09355) (7345.39943 7914.78133)))
("SF_MASONRY_AND_ARCH" 0 ((7345.39943 904.97738) (7345.39943 882.35294)))
("SF_MASONRY_AND_ARCH" 0 ((7345.39943 904.97738) (7364.25339 912.51980)))
("SF_PLANTING" 0 ((7345.39943 882.35294) (7356.71165 878.58314)))
("SF_PLANTING" 0 ((7371.79514 361.99095) (7363.05543 384.61538) (7349.17070 399.69740)))
("SF_PLANTING" 0 ((7356.71165 426.09446) (7350.22704 414.78224) (7349.17070 399.69740)))
("SF_PLANTING" 0 ((7379.33609 6979.63801) (7352.94118 7006.03292)))
("SF_PLANTING" 0 ((7368.02387 7039.96957) (7366.81980 7024.88688) (7352.94118 7006.03292)))
("SF_PLANTING" 0 ((7352.94118 825.79186) (7375.56561 822.02206) (7401.96052 825.79186)))
("SF_PLANTING" 0 ((7352.94118 825.79186) (7356.71165 878.58314)))
("SF_PLANTING" 0 ((7352.94118 622.17195) (7350.38167 633.47794) (7360.48292 641.02658)))
("SF_PLANTING" 0 ((7352.94118 622.17195) (7363.04231 629.71923) (7360.48292 641.02658)))
("SF_SOLAR" 0 ((7356.71165 8103.31833) (7371.79514 8092.00611)))
("SF_MASONRY_AND_ARCH" 0 ((7462.29287 897.43495) (7447.20939 901.05226) (7409.50226 882.50758) (7356.71165 878.58314)))
("SF_PLANTING" 0 ((7360.48292 493.96776) (7367.86923 478.88292) (7356.71165 426.09446)))
("SF_PLANTING" 0 ((7356.71165 426.09446) (7394.41957 429.86425)))
("SF_MASONRY_AND_ARCH" 0 ((7594.26753 1266.96833) (7582.95532 1263.34559) (7492.45826 1263.05011) (7443.43891
1253.08348) (7379.33609 1255.64989) (7360.48292 1251.88631)))
("SF_PLANTING" 0 ((7371.79514 656.10860) (7365.30283 652.18348) (7360.48292 641.02658)))
("SF_PLANTING" 0 ((7360.48292 493.96776) (7368.17240 504.22975) (7401.96052 522.24830)))
("SF_SOLAR" 0 ((7368.02387 8054.29864) (7368.02387 8046.75724)))
("SF_SOLAR" 0 ((7368.02387 7978.88394) (7368.02387 7993.96674)))
("SF_SOLAR" 0 ((7368.02387 7963.80090) (7368.02387 7948.71799)))
("SF_SOLAR" 0 ((7368.02387 7918.55204) (7368.02387 7926.09355)))
("SF_PLANTING" 0 ((7368.02387 6915.53518) (7368.02387 6904.22296)))
("SF_PLANTING" 0 ((7368.02387 6915.53518) (7368.17161 6949.47183) (7379.33609 6972.09627)))
("SF_PLANTING" 0 ((7443.43891 6896.68201) (7434.69932 6915.38077) (7428.34932 6919.15158) (7383.10735 6919.15814)
(7368.02387 6915.53518)))
("SF_PLANTING" 0 ((7368.02387 6904.22296) (7372.84457 6885.36980) (7386.87783 6862.74536)))
("SF_MASONRY_AND_ARCH" 0 ((7368.02410 3110.85973) (7368.02410 3009.04977) (7383.10735 2993.96708)))
("SF_MASONRY_AND_ARCH" 0 ((7368.02410 3110.85973) (7401.96075 3114.63020)))
("SF_MASONRY_AND_ARCH" 0 ((7368.02410 2575.41505) (7368.02410 2549.01934)))
("SF_MASONRY_AND_ARCH" 0 ((7368.02410 2575.41505) (7368.02410 2590.49774) (7368.02410 2865.76143) (7379.33609
2884.61538)))
("SF_MASONRY_AND_ARCH" 0 ((7390.64830 2884.61538) (7401.96075 2861.99095) (7401.96075 2556.56799) (7394.41267
2549.17398) (7368.02410 2549.01934)))
("SF_SOLAR" 0 ((7379.33609 8073.15226) (7371.79514 8092.00611)))
("SF_SOLAR" 0 ((7371.79514 8092.00611) (7386.87783 8099.54751)))
("SF_MASONRY_AND_ARCH" 0 ((7503.77048 1104.82749) (7499.84536 1093.66855) (7492.45826 1089.89796) (7383.10735
1089.73778) (7371.79514 1085.97285)))
("SF_MASONRY_AND_ARCH" 0 ((7371.79514 1055.80600) (7369.22183 1048.25882) (7375.56561 1018.09955)))
("SF_PLANTING" 0 ((7371.79514 656.10860) (7379.33609 656.10860)))
("SF_PLANTING" 0 ((7371.79514 656.10860) (7372.85147 678.73303) (7391.84627 723.98190) (7417.19174 757.91855)
(7462.44061 806.78394) (7488.68778 818.24943)))
("SF_PLANTING" 0 ((7390.64830 358.22115) (7371.79514 361.99095)))
("SF_MASONRY_AND_ARCH" 0 ((7375.56561 1127.45192) (7375.56561 1161.38857)))
("SF_MASONRY_AND_ARCH" 0 ((7462.29287 1161.38857) (7443.43891 1165.15837) (7386.87783 1164.86222) (7375.56561
1161.38857)))
("SF_MASONRY_AND_ARCH" 0 ((7481.14604 1036.95419) (7454.75113 1022.92025) (7409.50226 1014.47681) (7375.56561
1018.09955)))
("SF_PLANTING" 0 ((7379.33609 7073.90622) (7379.33609 7066.36527)))
("SF_PLANTING" 0 ((7379.33609 6979.63801) (7379.33609 6972.09627)))
("SF_PLANTING" 0 ((7379.33609 6979.63801) (7409.50226 7013.57466)))
("SF_PLANTING" 0 ((7443.43891 6945.70136) (7409.50226 6963.50543) (7379.33609 6972.09627)))
("SF_MASONRY_AND_ARCH" 0 ((7390.64830 2884.61538) (7379.33609 2884.61538)))
("SF_MASONRY_AND_ARCH" 0 ((7379.33609 2884.61538) (7368.02410 2899.69808) (7368.02410 2929.86425) (7368.02410
2952.48179) (7383.10735 2960.03043)))
("SF_MASONRY_AND_ARCH" 0 ((7383.10735 2993.96708) (7383.10735 2960.03043)))
("SF_MASONRY_AND_ARCH" 0 ((7401.96075 3114.63020) (7401.96075 3012.82025) (7383.10735 2993.96708)))
("SF_MASONRY_AND_ARCH" 0 ((7390.64830 2884.61538) (7401.96075 2903.46934) (7401.96075 2929.86425) (7401.96075
2948.71821) (7383.10735 2960.03043)))
("SF_PLANTING" 0 ((7386.87783 6855.20362) (7386.87783 6862.74536)))
("SF_PLANTING" 0 ((7443.43891 6896.68201) (7432.12048 6882.65532) (7401.96052 6872.85328) (7386.87783 6862.74536)))
("SF_PLANTING" 0 ((7386.87783 6855.20362) (7405.73179 6841.31844) (7417.04400 6838.44932) (7473.60509 6836.35622)
(7492.45826 6840.12093)))
("SF_PLANTING" 0 ((7386.87783 312.97229) (7420.81448 245.09898)))
("SF_PLANTING" 0 ((7386.87783 312.97229) (7391.69785 324.12919) (7398.19005 328.05430)))
("SF_SOLAR" 0 ((7390.64830 7960.03020) (7390.64830 7948.71799)))
("SF_PLANTING" 0 ((7390.64830 358.22115) (7398.19005 328.05430)))
("SF_PLANTING" 0 ((7390.64830 358.22115) (7394.41957 392.15781)))
("SF_SOLAR" 0 ((7394.41957 8058.06946) (7405.73179 8039.21561)))
("SF_SOLAR" 0 ((7409.50226 8065.61086) (7394.41957 8058.06946)))
("SF_SOLAR" 0 ((7394.41957 7982.65452) (7394.41957 7993.96674)))
("SF_SOLAR" 0 ((7405.73179 7874.56007) (7404.52760 7884.52319) (7394.41957 7895.92760)))
("SF_SOLAR" 0 ((7394.41957 7895.92760) (7405.73179 7903.30792) (7420.81448 7899.84638) (7488.68778 7899.69830)
(7515.08269 7903.46912)))
("SF_PLANTING" 0 ((7420.81448 403.47002) (7405.73801 407.39446) (7394.41957 429.86425)))
("SF_PLANTING" 0 ((7394.41957 429.86425) (7405.87952 448.71889) (7481.14604 524.13179)))
("SF_ARCHITECTURE" 0 ((7428.35622 5705.12828) (7398.19005 5705.12828)))
("SF_ARCHITECTURE" 0 ((7398.19005 5705.12828) (7394.42579 5659.87941) (7394.42579 3853.69491) (7401.96052 3834.84163)))
("SF_PLANTING" 0 ((7398.19005 328.05430) (7424.43722 315.69265) (7458.52161 275.26301)))
("SF_PLANTING" 0 ((7401.96052 522.24830) (7413.27274 501.50735)))
("SF_PLANTING" 0 ((7401.96052 522.24830) (7398.48620 531.60656) (7403.01697 550.52885) (7434.84084 610.85973)
(7448.26584 667.42081) (7491.40192 791.85520) (7492.31052 810.70226) (7488.68778 818.24943)))
("SF_PLANTING" 0 ((7401.96052 522.24830) (7428.35622 536.50113) (7454.75113 561.69265) (7518.85396 606.03971)
(7564.10283 628.65724) (7586.72794 629.71437)))
("SF_SOLAR" 0 ((7413.27274 8016.59118) (7405.73179 8039.21561)))
("SF_SOLAR" 0 ((7424.58495 8042.98643) (7405.73179 8039.21561)))
("SF_PLANTING" 0 ((7409.50226 7013.57466) (7420.81448 7009.80419)))
("SF_PLANTING" 0 ((7469.83382 7111.61414) (7451.12839 7096.52410) (7421.86391 7051.28179) (7410.55860 7028.65735)
(7409.50226 7013.57466)))
("SF_SOLAR" 0 ((7413.27274 7963.80090) (7413.27274 7952.48869)))
("SF_MASONRY_AND_ARCH" 0 ((7413.27274 1896.68201) (7414.47070 1907.98733) (7420.81448 1915.53518)))
("SF_MASONRY_AND_ARCH" 0 ((7417.04400 1866.51584) (7413.27274 1877.82805)))
("SF_MASONRY_AND_ARCH" 0 ((7417.04400 1866.51584) (7435.89717 1862.74536)))
("SF_PLANTING" 0 ((7420.81448 403.47002) (7428.51086 384.76312) (7450.98066 373.30317)))
("SF_PLANTING" 0 ((7420.81448 403.47002) (7443.43891 414.78224)))
("SF_PLANTING" 0 ((7462.29287 260.18100) (7447.20939 246.30238) (7420.81448 245.09898)))
("SF_MASONRY_AND_ARCH" 0 ((7424.58495 2013.57466) (7413.42738 2002.25622) (7413.42738 1968.32579) (7420.82138
1958.21776) (7439.66844 1953.39084) (7613.12217 1953.24932) (7639.51640 1957.01357) (7658.37104 1953.39084) (7726.24434
1953.24310)))
("SF_MASONRY_AND_ARCH" 0 ((7435.89717 1621.41686) (7424.58495 1625.18948)))
("SF_MASONRY_AND_ARCH" 0 ((7428.35622 1644.04129) (7424.58495 1625.18948)))
("SF_SOLAR" 0 ((7439.66844 7982.65452) (7428.35622 8005.27896)))
("SF_SOLAR" 0 ((7428.35622 8005.27896) (7447.20939 8009.04977)))
("SF_ARCHITECTURE" 0 ((7428.35622 5705.12828) (7428.35000 3947.96380) (7424.58495 3925.33937) (7428.20848 3906.48609)
(7428.35622 3838.61278)))
("SF_ARCHITECTURE" 0 ((7466.06335 5705.12828) (7450.98066 5708.89887) (7428.35622 5705.12828)))
("SF_SOLAR" 0 ((7435.89717 7926.09355) (7435.89717 7914.78133)))
("SF_MASONRY_AND_ARCH" 0 ((7435.89717 1372.54808) (7439.66844 1365.00848)))
("SF_PLANTING" 0 ((7439.66844 7006.03292) (7443.43891 7002.26244) (7454.75113 7002.26244)))
("SF_PLANTING" 0 ((7488.68778 6896.68201) (7443.43891 6896.68201)))
("SF_PLANTING" 0 ((7443.43891 414.78224) (7450.83292 392.15781) (7450.98066 373.30317)))
("SF_PLANTING" 0 ((7522.62443 490.19514) (7492.45826 474.96471) (7454.89887 437.40667) (7443.43891 414.78224)))
("SF_PLANTING" 0 ((7458.52161 358.22115) (7450.98066 365.76075) (7450.98066 373.30317)))
("SF_PLANTING" 0 ((7454.75113 7002.26244) (7459.71957 6983.40848) (7487.63145 6949.47183) (7500.00000 6923.07692)))
("SF_PLANTING" 0 ((7545.24887 6972.09627) (7533.93665 6973.30057) (7503.77048 6997.43552) (7481.14604 7008.74774)
(7466.06335 7009.64932) (7454.75113 7002.26244)))
("SF_MASONRY_AND_ARCH" 0 ((7492.45826 2779.03495) (7481.14604 2772.54955) (7454.75113 2767.72274)))
("SF_MASONRY_AND_ARCH" 0 ((7696.07749 2500.00000) (7669.68326 2507.53552) (7647.05882 2503.92511) (7628.20419
2507.53552) (7466.06335 2507.53552) (7454.75113 2503.77048)))
("SF_MASONRY_AND_ARCH" 0 ((7458.52161 2375.56561) (7452.32624 2383.11357) (7454.75113 2417.04400)))
("SF_MASONRY_AND_ARCH" 0 ((7454.75113 2417.04400) (7473.60509 2420.80826) (7594.26267 2420.96912) (7605.57975
2428.35622)))
("SF_SOLAR" 0 ((7458.52161 7971.34231) (7469.83382 7975.11312)))
("SF_MASONRY_AND_ARCH" 0 ((7458.52161 3412.51912) (7458.52161 3404.97738)))
("SF_MASONRY_AND_ARCH" 0 ((7865.76075 3340.87455) (7631.97681 3341.02919) (7620.66459 3344.34955) (7601.80995
3340.87455) (7481.14604 3340.88077) (7466.07025 3344.34955) (7458.52161 3340.87455)))
("SF_MASONRY_AND_ARCH" 0 ((7869.53337 3273.00124) (7858.22115 3276.62477) (7786.57523 3276.76629) (7771.49321
3273.29751) (7756.41120 3276.61787) (7737.55656 3270.42873) (7722.47455 3272.84661) (7707.38971 3269.23699) (7665.91346
3269.37851) (7650.82862 3272.99502) (7609.35238 3272.85351) (7594.26753 3269.23699) (7549.01934 3271.80339) (7511.31222
3255.35215) (7466.07025 3258.06629) (7458.52161 3261.68903)))
("SF_MASONRY_AND_ARCH" 0 ((7458.52161 3190.04525) (7469.83382 3186.28100) (7541.47839 3189.89751) (7582.95532
3182.79977) (7598.04016 3186.26855) (7680.99548 3186.42251) (7748.86878 3193.80882) (7790.34785 3186.42251) (7835.59672
3186.42251) (7869.53337 3193.81572)))
("SF_MASONRY_AND_ARCH" 0 ((7500.00000 2820.51256) (7492.45204 2816.88982) (7458.52161 2816.74208)))
("SF_MASONRY_AND_ARCH" 0 ((7458.52161 2631.97613) (7473.60509 2635.74661) (7601.80995 2635.74038) (7616.89197
2631.97613)))
("SF_MASONRY_AND_ARCH" 0 ((7462.29287 2564.10283) (7458.52161 2575.41505)))
("SF_MASONRY_AND_ARCH" 0 ((7458.52161 1862.74536) (7484.91041 1862.59072) (7491.25419 1858.81946) (7492.45826
1809.95475)))
("SF_PLANTING" 0 ((7458.52161 358.22115) (7463.34921 328.05430) (7473.60509 309.19966)))
("SF_PLANTING" 0 ((7511.31222 392.15781) (7484.91731 370.58903) (7458.52161 358.22115)))
("SF_PLANTING" 0 ((7462.29287 260.18100) (7458.52161 263.95079) (7458.52161 275.26301)))
("SF_PLANTING" 0 ((7458.52161 275.26301) (7472.40090 290.34785) (7473.60509 309.19966)))
("SF_MASONRY_AND_ARCH" 0 ((7869.53337 2892.15713) (7854.44853 2895.92138) (7790.34785 2895.77919) (7763.95079
2890.48552) (7703.61991 2895.92138) (7605.57975 2895.92070) (7560.33156 2889.58382) (7511.31222 2895.77986) (7462.29287
2895.92760)))
("SF_PLANTING" 0 ((7462.29287 260.18100) (7481.14604 260.18100)))
("SF_ARCHITECTURE" 0 ((7466.06335 5705.12828) (7466.06335 3966.81708) (7466.06335 3944.19265) (7466.06335 3849.92500)
(7466.06335 3831.07048)))
("SF_ARCHITECTURE" 0 ((7466.06335 5705.12828) (7484.91731 5708.89887) (7503.77070 5705.12828)))
("SF_MASONRY_AND_ARCH" 0 ((7466.06335 3122.17195) (7533.93665 3118.40147)))
("SF_MASONRY_AND_ARCH" 0 ((7466.06335 3046.75690) (7650.82862 3046.75690)))
("SF_MASONRY_AND_ARCH" 0 ((7466.06335 2967.57138) (7579.18552 2967.57760) (7598.04016 2971.34265)))
("SF_MASONRY_AND_ARCH" 0 ((7469.83382 1421.56957) (7466.06335 1402.71493)))
("SF_MASONRY_AND_ARCH" 0 ((7861.99095 1417.79695) (7726.24434 1415.22511) (7692.30769 1425.19095) (7628.20419
1425.48710) (7613.12217 1429.10430) (7571.64378 1428.96210) (7560.33156 1425.49400) (7541.47839 1428.95588) (7469.83382
1421.56957)))
("SF_MASONRY_AND_ARCH" 0 ((7473.60509 2187.02839) (7477.22093 2202.11188) (7473.60509 2217.19457)))
("SF_MASONRY_AND_ARCH" 0 ((7473.60509 2187.02839) (7477.37557 2187.02839) (7481.14604 2179.48744)))
("SF_PLANTING" 0 ((7500.00000 309.19966) (7473.60509 309.19966)))
("SF_SOLAR" 0 ((7477.37557 7926.09355) (7481.14604 7914.78133)))
("SF_MASONRY_AND_ARCH" 0 ((7477.37557 2153.09174) (7481.14604 2179.48744)))
("SF_MASONRY_AND_ARCH" 0 ((7477.37557 1617.64706) (7522.62443 1617.64706)))
("SF_MASONRY_AND_ARCH" 0 ((7477.37557 1161.38857) (7492.45826 1161.38857)))
("SF_MASONRY_AND_ARCH" 0 ((7707.38971 2175.71618) (7654.60124 2179.48054) (7628.20419 2175.72308) (7609.35238
2179.48122) (7481.14604 2179.48744)))
("SF_PLANTING" 0 ((7481.14604 260.18100) (7500.00000 237.71120) (7518.85396 230.16256) (7560.33156 230.16946)
(7579.18552 245.09898)))
("SF_PLANTING" 0 ((7507.54174 286.57523) (7481.14604 260.18100)))
("SF_MASONRY_AND_ARCH" 0 ((7601.80995 2326.54627) (7594.26267 2322.92274) (7500.00000 2321.72557) (7486.12138
2315.07941) (7484.91731 2296.38009)))
("SF_PLANTING" 0 ((7488.68778 6896.68201) (7495.03156 6877.82805) (7492.45826 6840.12093)))
("SF_PLANTING" 0 ((7488.68778 6896.68201) (7500.00000 6923.07692)))
("SF_PLANTING" 0 ((7488.68778 818.24943) (7492.45826 825.79186)))
("SF_PLANTING" 0 ((7492.45826 6840.12093) (7511.31222 6828.80871)))
("SF_MASONRY_AND_ARCH" 0 ((7492.45826 2779.03495) (7492.45826 2786.57590)))
("SF_MASONRY_AND_ARCH" 0 ((7492.45826 2779.03495) (7511.31222 2775.26369)))
("SF_MASONRY_AND_ARCH" 0 ((7496.22952 1742.08145) (7492.60600 1753.39367) (7492.45826 1809.95475)))
("SF_MASONRY_AND_ARCH" 0 ((7492.45826 1161.38857) (7526.39491 1161.38857)))
("SF_MASONRY_AND_ARCH" 0 ((7492.45826 1161.38857) (7492.45826 1153.84615)))
("SF_MASONRY_AND_ARCH" 0 ((7500.00000 3152.33812) (7496.22952 3159.87907)))
("SF_MASONRY_AND_ARCH" 0 ((7496.22952 1742.08145) (7564.09593 1738.15633) (7570.43971 1734.38575) (7571.64378
1723.22681)))
("SF_PLANTING" 0 ((7579.18552 6915.53518) (7564.10283 6911.92613) (7549.01934 6919.15158) (7500.00000 6923.07692)))
("SF_MASONRY_AND_ARCH" 0 ((7503.77048 1104.82749) (7500.00000 1119.90950)))
("SF_PLANTING" 0 ((7507.54174 309.19966) (7500.00000 309.19966)))
("SF_PLANTING" 0 ((7522.62443 339.36652) (7504.82692 327.89966) (7500.00000 309.19966)))
("SF_PLANTING" 0 ((7503.77048 7070.13575) (7547.81527 6994.72070) (7545.24887 6972.09627)))
("SF_PLANTING" 0 ((7564.10283 6776.01810) (7503.77048 6779.78857)))
("SF_PLANTING" 0 ((7503.77048 6779.78857) (7503.91821 6798.64253) (7511.31222 6828.80871)))
("SF_MASONRY_AND_ARCH" 0 ((7503.77048 1104.82749) (7628.20419 1104.82749)))
("SF_PLANTING" 0 ((7511.31222 392.15781) (7503.77048 411.00962)))
("SF_ARCHITECTURE" 0 ((7530.16618 5705.12828) (7503.77070 5705.12828)))
("SF_ARCHITECTURE" 0 ((7518.85396 5282.80543) (7503.77070 5294.11765) (7503.77070 5309.20102) (7503.77070 5705.12828)))
("SF_MASONRY_AND_ARCH" 0 ((7530.16618 904.97738) (7511.46686 895.91256) (7507.54174 901.20758)))
("SF_PLANTING" 0 ((7507.54174 286.57523) (7507.54174 309.19966)))
("SF_PLANTING" 0 ((7507.54174 309.19966) (7525.33857 324.28450) (7530.16618 339.36652)))
("SF_PLANTING" 0 ((7507.54174 286.57523) (7533.93665 279.03563)))
("SF_PLANTING" 0 ((7511.31222 6828.80871) (7526.39491 6833.62862) (7586.72794 6874.05758)))
("SF_MASONRY_AND_ARCH" 0 ((7511.31222 1033.18156) (7518.86018 1029.55950) (7571.64378 1025.64197)))
("SF_PLANTING" 0 ((7511.31222 392.15781) (7545.24887 399.69740)))
("SF_SOLAR" 0 ((7515.08269 7903.46912) (7526.39491 7895.92760)))
("SF_SOLAR" 0 ((7518.85396 7911.01052) (7515.08269 7903.46912)))
("SF_ARCHITECTURE" 0 ((7518.85396 5282.80543) (7518.85396 5030.16550)))
("SF_ARCHITECTURE" 0 ((7518.85396 5282.80543) (7528.96199 5294.11765) (7530.17240 5569.38201) (7537.70735 5592.00645)
(7530.16618 5622.17195) (7537.70735 5690.04525) (7530.16618 5705.12828)))
("SF_ARCHITECTURE" 0 ((7518.85396 5030.16550) (7518.85396 5022.62443)))
("SF_ARCHITECTURE" 0 ((7518.85396 5030.16550) (7511.31222 5026.39559) (7518.85396 5022.62443)))
("SF_ARCHITECTURE" 0 ((7518.85396 5022.62443) (7518.85396 5003.77115)))
("SF_ARCHITECTURE" 0 ((7518.85396 4819.00452) (7528.96199 4830.31674) (7530.01154 4992.45826) (7518.85396 5003.77115)))
("SF_ARCHITECTURE" 0 ((7518.85396 4819.00452) (7503.77070 4834.08790) (7503.77070 4984.91663) (7511.45373 4999.84536)
(7518.85396 5003.77115)))
("SF_ARCHITECTURE" 0 ((7518.85396 4819.00452) (7518.85396 4796.38009)))
("SF_ARCHITECTURE" 0 ((7518.85396 4181.74921) (7528.96199 4193.06210) (7530.15928 4781.29672) (7526.24717 4792.45498)
(7518.85396 4796.38009)))
("SF_ARCHITECTURE" 0 ((7518.85396 4181.74921) (7503.77070 4196.83258) (7503.77070 4773.75566) (7503.77070 4788.83213)
(7518.85396 4796.38009)))
("SF_ARCHITECTURE" 0 ((7518.85396 4181.74921) (7518.85396 4174.20814)))
("SF_PLANTING" 0 ((7518.85396 550.52885) (7528.28054 552.41233)))
("SF_PLANTING" 0 ((7522.62443 339.36652) (7518.85396 343.13631) (7518.85396 354.44853)))
("SF_PLANTING" 0 ((7522.62443 490.19514) (7549.01934 418.55204)))
("SF_PLANTING" 0 ((7522.62443 490.19514) (7537.70713 508.90204) (7575.26652 539.22149) (7598.18722 569.38066)
(7628.05713 599.54751) (7638.31923 614.62952) (7643.12670 637.24910) (7639.36312 643.59152) (7620.66459 644.64864)
(7586.72794 629.71437)))
("SF_PLANTING" 0 ((7522.62443 339.36652) (7530.16618 339.36652)))
("SF_PLANTING" 0 ((7526.39491 6666.66640) (7535.14084 6696.83258) (7552.79061 6715.68654)))
("SF_MASONRY_AND_ARCH" 0 ((7526.39491 2775.26369) (7579.18552 2782.80543) (7628.20419 2780.70645) (7650.82862
2775.26369)))
("SF_PLANTING" 0 ((7643.28903 723.98190) (7616.89197 731.51742) (7541.47839 731.37590) (7526.39491 727.75170)))
("SF_PLANTING" 0 ((7526.39491 539.21663) (7528.28054 552.41233)))
("SF_PLANTING" 0 ((7528.28054 552.41233) (7533.93665 569.38066)))
("SF_PLANTING" 0 ((7545.24887 558.06844) (7528.28054 552.41233)))
("SF_ARCHITECTURE" 0 ((7579.18552 3797.13382) (7579.18552 5693.81606) (7575.26041 5704.97364) (7567.87330 5708.74412)
(7530.16618 5705.12828)))
("SF_PLANTING" 0 ((7565.98767 352.56505) (7530.16618 339.36652)))
("SF_PLANTING" 0 ((7541.47839 6889.14027) (7533.93665 6885.36980)))
("SF_PLANTING" 0 ((7533.93665 6738.31097) (7552.79061 6723.22749)))
("SF_PLANTING" 0 ((7533.93665 6481.90045) (7631.97681 6478.12964)))
("SF_PLANTING" 0 ((7577.29989 6570.51256) (7582.73371 6561.15351) (7581.75192 6538.46154) (7571.64378 6528.35362)
(7545.24887 6526.99446) (7537.86176 6523.22398) (7534.09129 6515.83710) (7533.93665 6481.90045)))
("SF_MASONRY_AND_ARCH" 0 ((7533.93665 1862.74536) (7601.80995 1862.74536)))
("SF_MASONRY_AND_ARCH" 0 ((7537.70713 2266.21391) (7549.01934 2269.97896) (7688.53790 2269.98518)))
("SF_MASONRY_AND_ARCH" 0 ((7537.70713 1161.38857) (7545.25577 1165.01063) (7579.17862 1161.54186) (7586.72794
1165.15837)))
("SF_MASONRY_AND_ARCH" 0 ((7703.61991 1813.72455) (7541.47839 1813.72455)))
("SF_PLANTING" 0 ((7579.18552 6926.84740) (7550.07579 6960.78405) (7545.24887 6972.09627)))
("SF_PLANTING" 0 ((7565.98767 352.56505) (7557.82602 361.92330) (7551.59265 392.15023) (7545.24887 399.69740)))
("SF_PLANTING" 0 ((7549.01934 418.55204) (7545.24887 399.69740)))
("SF_MASONRY_AND_ARCH" 0 ((7549.01934 901.20758) (7552.79061 893.66516)))
("SF_PLANTING" 0 ((7549.01934 822.02206) (7673.45305 822.02206)))
("SF_PLANTING" 0 ((7586.72794 629.71437) (7582.80204 610.85973) (7549.01934 584.46550)))
("SF_PLANTING" 0 ((7579.18552 418.55204) (7549.01934 418.55204)))
("SF_PLANTING" 0 ((7552.79061 6715.68654) (7552.79061 6723.22749)))
("SF_PLANTING" 0 ((7575.41505 6734.53971) (7552.79061 6723.22749)))
("SF_PLANTING" 0 ((7609.35238 6711.91527) (7579.18552 6693.36471) (7552.79061 6715.68654)))
("SF_PLANTING" 0 ((7577.29989 6570.51256) (7531.37025 6580.09434) (7531.22251 6591.25215) (7547.82149 6613.87658)
(7552.79061 6628.95928)))
("SF_MASONRY_AND_ARCH" 0 ((7560.33156 2846.90826) (7560.33156 2854.44921)))
("SF_MASONRY_AND_ARCH" 0 ((7560.33156 2824.28382) (7564.10283 2816.74208)))
("SF_MASONRY_AND_ARCH" 0 ((7560.33156 1617.64706) (7569.21900 1624.88563) (7571.64378 1644.04129)))
("SF_PLANTING" 0 ((7560.33156 267.72342) (7564.10283 263.95079) (7575.41505 263.95079)))
("SF_PLANTING" 0 ((7575.41505 6772.24762) (7564.10283 6776.01810)))
("SF_PLANTING" 0 ((7564.10283 6776.01810) (7568.92964 6806.18428) (7586.72794 6828.80871)))
("SF_MASONRY_AND_ARCH" 0 ((7865.76075 3099.54751) (7684.76527 3099.55373) (7616.89197 3105.89129) (7582.95532
3103.46572) (7564.10283 3110.85973)))
("SF_PLANTING" 0 ((7579.18552 316.74208) (7572.83484 320.66719) (7565.98767 352.56505)))
("SF_PLANTING" 0 ((7565.98767 352.56505) (7571.64378 358.22115) (7582.95532 358.22115)))
("SF_SOLAR" 0 ((7571.64378 7914.78133) (7579.18552 7903.46912)))
("SF_PLANTING" 0 ((7571.64378 6987.17975) (7579.18552 6983.40848)))
("SF_MASONRY_AND_ARCH" 0 ((7861.99095 1674.20814) (7854.44367 1670.58541) (7828.05430 1670.43835) (7805.42986
1674.20192) (7748.86878 1671.63552) (7639.51640 1676.78077) (7582.95532 1674.36278) (7572.84796 1681.75543) (7571.64378
1708.14480)))
("SF_MASONRY_AND_ARCH" 0 ((7571.64378 1006.78733) (7571.64378 1025.64197)))
("SF_MASONRY_AND_ARCH" 0 ((7571.64378 1025.64197) (7635.74661 1038.61810) (7745.09898 1036.80577) (7756.41120
1033.33688) (7775.26301 1036.94038) (7805.42986 1033.18156) (7861.99095 1036.95419)))
("SF_PLANTING" 0 ((7575.41505 6772.24762) (7575.41505 6734.53971)))
("SF_PLANTING" 0 ((7575.41505 6772.24762) (7635.74661 6779.78857)))
("SF_PLANTING" 0 ((7609.35238 6723.22749) (7575.41505 6734.53971)))
("SF_MASONRY_AND_ARCH" 0 ((7575.41505 867.27093) (7575.56278 908.74717) (7579.18552 920.05939)))
("SF_PLANTING" 0 ((7575.41505 263.95079) (7579.18552 245.09898)))
("SF_PLANTING" 0 ((7575.41505 263.95079) (7579.03778 271.50011) (7579.18552 316.74208)))
("SF_PLANTING" 0 ((7579.18552 6598.79310) (7577.29989 6570.51256)))
("SF_PLANTING" 0 ((7577.29989 6570.51256) (7594.26753 6577.22511) (7605.57975 6591.25215)))
("SF_PLANTING" 0 ((7579.18552 6983.40848) (7598.18722 6953.24966) (7609.35238 6945.70136)))
("SF_PLANTING" 0 ((7582.95532 6998.49197) (7582.95532 6987.17975) (7579.18552 6983.40848)))
("SF_PLANTING" 0 ((7579.18552 6915.53518) (7579.18552 6926.84740)))
("SF_PLANTING" 0 ((7579.18552 6926.84740) (7609.35238 6938.15962)))
("SF_PLANTING" 0 ((7579.18552 6915.53518) (7586.72794 6874.05758)))
("SF_ARCHITECTURE" 0 ((7579.18552 3797.13382) (7598.04016 3793.36391) (7684.76527 3793.37014) (7703.61991 3797.12760)
(7726.24434 3793.37014) (7929.86425 3793.37014) (7944.94627 3797.13382)))
("SF_MASONRY_AND_ARCH" 0 ((7579.18552 961.53846) (7711.16233 961.53224) (7733.78676 957.77489) (7763.95079 965.01278)
(7782.80543 957.91640) (7835.59672 957.76867)))
("SF_PLANTING" 0 ((7579.18552 418.55204) (7590.34310 399.69740) (7590.34932 377.07296) (7582.95532 358.22115)))
("SF_PLANTING" 0 ((7579.18552 418.55204) (7598.18722 448.56357) (7613.12217 452.48869)))
("SF_PLANTING" 0 ((7579.18552 316.74208) (7593.06414 328.05430) (7594.26753 339.36652)))
("SF_PLANTING" 0 ((7631.97681 245.09898) (7579.18552 245.09898)))
("SF_PLANTING" 0 ((7582.95532 6998.49197) (7616.89197 6998.49197)))
("SF_PLANTING" 0 ((7582.95532 6998.49197) (7575.56346 7032.42862) (7586.72794 7055.05305)))
("SF_ARCHITECTURE" 0 ((7888.38518 5799.39661) (7850.67873 5795.62602) (7631.97681 5795.92195) (7613.12217 5799.39005)
(7582.95532 5795.62602)))
("SF_PLANTING" 0 ((7582.95532 358.22115) (7594.26753 339.36652)))
("SF_PLANTING" 0 ((7635.74661 6866.51584) (7586.72794 6874.05758)))
("SF_PLANTING" 0 ((7594.26753 6632.72975) (7601.81686 6646.75645) (7624.43439 6651.58371)))
("SF_MASONRY_AND_ARCH" 0 ((7594.26753 2450.98066) (7605.57975 2428.35622)))
("SF_PLANTING" 0 ((7601.80995 343.13631) (7594.26753 339.36652)))
("SF_MASONRY_AND_ARCH" 0 ((7639.51640 2428.35622) (7605.57975 2428.35622)))
("SF_PLANTING" 0 ((7616.89197 7006.03292) (7609.35238 7036.19910)))
("SF_PLANTING" 0 ((7609.35238 6938.15962) (7609.35238 6945.70136)))
("SF_PLANTING" 0 ((7616.89197 6998.49197) (7616.73869 6957.01357) (7609.35238 6945.70136)))
("SF_PLANTING" 0 ((7669.68326 6930.61867) (7609.35238 6938.15962)))
("SF_PLANTING" 0 ((7609.35238 6711.91527) (7609.35238 6723.22749)))
("SF_PLANTING" 0 ((7609.35238 6723.22749) (7623.37805 6734.54005) (7635.74661 6772.24762)))
("SF_PLANTING" 0 ((7609.35238 6711.91527) (7620.51618 6704.36742) (7627.14853 6693.06210) (7628.05713 6662.89593)
(7624.43439 6651.58371)))
("SF_PLANTING" 0 ((7609.35238 6414.02715) (7618.09061 6432.72602) (7628.20419 6436.65158)))
("SF_MASONRY_AND_ARCH" 0 ((7861.99095 2971.34265) (7748.86878 2971.33643) (7730.01414 2967.57828) (7703.61991
2971.33575) (7680.99548 2967.57138) (7609.35238 2971.34265)))
("SF_MASONRY_AND_ARCH" 0 ((7620.66459 2552.79061) (7613.12217 2552.79061)))
("SF_PLANTING" 0 ((7616.89197 429.86425) (7613.12217 452.48869)))
("SF_PLANTING" 0 ((7631.97681 467.57070) (7617.04729 459.88880) (7613.12217 452.48869)))
("SF_PLANTING" 0 ((7639.51640 7006.03292) (7616.89197 7006.03292)))
("SF_PLANTING" 0 ((7616.89197 6998.49197) (7616.89197 7006.03292)))
("SF_MASONRY_AND_ARCH" 0 ((7620.66459 2605.58043) (7616.89197 2631.97613)))
("SF_MASONRY_AND_ARCH" 0 ((7647.05882 2639.51708) (7616.89197 2631.97613)))
("SF_MASONRY_AND_ARCH" 0 ((7865.76075 1595.02262) (7846.90894 1591.25283) (7673.45305 1595.01640) (7616.89197
1587.48020)))
("SF_MASONRY_AND_ARCH" 0 ((7616.89197 1263.19853) (7635.74661 1263.19853)))
("SF_PLANTING" 0 ((7639.51640 7006.03292) (7646.90419 7021.11640) (7645.85396 7085.21188) (7635.74661 7091.54932)
(7609.49943 7082.80034) (7602.10611 7096.53066) (7606.78462 7115.38462) (7620.66459 7130.46731)))
("SF_MASONRY_AND_ARCH" 0 ((7620.66459 1538.46154) (7631.97681 1542.23133)))
("SF_MASONRY_AND_ARCH" 0 ((7620.66459 1474.35803) (7635.74661 1478.13066) (7692.30079 1471.78620) (7699.85011
1474.35803)))
("SF_PLANTING" 0 ((7665.91346 6595.02262) (7650.82862 6596.07862) (7629.40973 6606.48971) (7631.82839 6632.72975)
(7624.43439 6651.58371)))
("SF_MASONRY_AND_ARCH" 0 ((7624.43439 1742.08145) (7688.53790 1742.08145)))
("SF_PLANTING" 0 ((7647.05882 414.78224) (7631.98167 410.85633) (7621.71335 392.15781) (7617.19581 358.22115)
(7624.43439 346.90894)))
("SF_PLANTING" 0 ((7635.74661 297.88744) (7629.40283 301.81335) (7624.43439 331.82410)))
("SF_PLANTING" 0 ((7628.20419 6436.65158) (7665.91346 6429.11018)))
("SF_PLANTING" 0 ((7631.97681 6478.12964) (7628.20419 6436.65158)))
("SF_PLANTING" 0 ((7639.51640 6342.38303) (7625.63925 6353.69559) (7628.20419 6372.54910)))
("SF_MASONRY_AND_ARCH" 0 ((7628.20419 1244.34389) (7639.51640 1244.34389)))
("SF_MASONRY_AND_ARCH" 0 ((7628.20419 1134.99152) (7628.20419 1104.82749)))
("SF_MASONRY_AND_ARCH" 0 ((7631.97681 1070.89084) (7628.35260 1078.43801) (7628.20419 1104.82749)))
("SF_PLANTING" 0 ((7631.97681 6478.12964) (7650.82862 6481.90045)))
("SF_PLANTING" 0 ((7631.97681 6274.50973) (7639.51640 6297.13416)))
("SF_MASONRY_AND_ARCH" 0 ((7631.97681 2586.72726) (7809.19966 2586.72104) (7824.28450 2582.95600)))
("SF_MASONRY_AND_ARCH" 0 ((7635.74661 2077.67749) (7631.97681 2111.61391)))
("SF_MASONRY_AND_ARCH" 0 ((7631.97681 2111.61391) (7677.22568 2115.37839) (7748.86878 2111.61414) (7771.49321
2115.37839) (7861.99095 2115.38462)))
("SF_MASONRY_AND_ARCH" 0 ((7643.28903 2009.80419) (7638.31923 2028.50271) (7631.97681 2032.42862)))
("SF_MASONRY_AND_ARCH" 0 ((7865.76075 1161.38857) (7850.67873 1165.15215) (7631.97681 1165.15837)))
("SF_PLANTING" 0 ((7631.97681 467.57070) (7639.51640 463.80090)))
("SF_PLANTING" 0 ((7631.97681 467.57070) (7635.74661 475.11312)))
("SF_PLANTING" 0 ((7631.97681 245.09898) (7654.60124 230.16256) (7699.85011 230.16256) (7726.24434 241.32636)))
("SF_PLANTING" 0 ((7631.97681 245.09898) (7635.74661 297.88744)))
("SF_PLANTING" 0 ((7647.05882 6866.51584) (7635.74661 6866.51584)))
("SF_PLANTING" 0 ((7639.51640 6794.87206) (7635.89434 6802.41991) (7635.74661 6866.51584)))
("SF_PLANTING" 0 ((7635.74661 6779.78857) (7635.74661 6772.24762)))
("SF_PLANTING" 0 ((7639.51640 6794.87206) (7639.51640 6783.55984) (7635.74661 6779.78857)))
("SF_PLANTING" 0 ((7665.91346 6768.47636) (7635.74661 6772.24762)))
("SF_MASONRY_AND_ARCH" 0 ((7805.42986 3525.64129) (7647.05882 3525.79593) (7635.74661 3533.18224)))
("SF_MASONRY_AND_ARCH" 0 ((7635.74661 2371.79514) (7643.28903 2398.19005)))
("SF_MASONRY_AND_ARCH" 0 ((7635.74661 1263.19853) (7639.51640 1244.34389)))
("SF_MASONRY_AND_ARCH" 0 ((7635.74661 1263.19853) (7643.28903 1297.13518)))
("SF_PLANTING" 0 ((7635.74661 297.88744) (7649.63145 309.19966) (7665.91346 369.53337)))
("SF_PLANTING" 0 ((7639.51640 7006.03292) (7651.88575 6987.32726) (7669.68326 6972.09627)))
("SF_PLANTING" 0 ((7639.51640 6794.87206) (7665.90588 6797.43824) (7680.99548 6779.78857)))
("SF_PLANTING" 0 ((7650.82862 6500.75407) (7640.71505 6512.06663) (7632.13009 6538.46154) (7639.51640 6564.85645)))
("SF_MASONRY_AND_ARCH" 0 ((7639.51640 2428.35622) (7643.28903 2398.19005)))
("SF_MASONRY_AND_ARCH" 0 ((7639.51640 2428.35622) (7658.37104 2434.69932) (7688.53032 2430.92251) (7695.92421
2420.81448) (7696.07749 2401.96052)))
("SF_MASONRY_AND_ARCH" 0 ((7861.99095 2319.00452) (7809.19966 2318.84989) (7797.88744 2315.53020) (7767.72342
2324.44038) (7677.22568 2322.92964) (7650.82862 2326.70090) (7640.72127 2334.09412) (7639.51640 2352.94118)))
("SF_MASONRY_AND_ARCH" 0 ((7643.28903 2009.80419) (7639.51640 1990.95023)))
("SF_MASONRY_AND_ARCH" 0 ((7639.51640 1858.97410) (7707.38971 1870.28631)))
("SF_MASONRY_AND_ARCH" 0 ((7643.28903 1297.13518) (7639.51640 1308.44740)))
("SF_MASONRY_AND_ARCH" 0 ((7647.05882 1229.26188) (7639.51640 1244.34389)))
("SF_MASONRY_AND_ARCH" 0 ((7643.28903 2398.19005) (7696.07749 2401.96052)))
("SF_MASONRY_AND_ARCH" 0 ((7643.28903 2009.80419) (7669.68326 2013.57466) (7850.67873 2013.56844) (7865.76075
2009.80419)))
("SF_MASONRY_AND_ARCH" 0 ((7643.28903 1297.13518) (7688.53790 1297.13518)))
("SF_MASONRY_AND_ARCH" 0 ((7643.28903 1199.09502) (7647.05882 1229.26188)))
("SF_PLANTING" 0 ((7643.28903 723.98190) (7639.82025 712.66968) (7647.05882 701.35747)))
("SF_PLANTING" 0 ((7643.28903 723.98190) (7650.83620 727.60464) (7699.85011 727.90011) (7711.16233 731.36900)
(7775.26301 724.13654) (7816.74208 727.75170) (7850.67873 724.12964) (7861.99095 727.75170)))
("SF_PLANTING" 0 ((7703.61991 6858.97410) (7654.60611 6859.12896) (7647.05882 6866.51584)))
("SF_PLANTING" 0 ((7673.45305 6923.07692) (7659.56900 6907.99423) (7647.05882 6866.51584)))
("SF_MASONRY_AND_ARCH" 0 ((7647.05882 3416.28959) (7647.05882 3423.83133)))
("SF_MASONRY_AND_ARCH" 0 ((7647.05882 3397.43563) (7654.60611 3390.04932) (7688.53790 3389.74695) (7699.85011
3386.12342)))
("SF_MASONRY_AND_ARCH" 0 ((7647.05882 2639.51708) (7658.37104 2635.75283) (7831.82410 2635.74038) (7850.67873
2631.98235) (7869.53337 2635.74661)))
("SF_MASONRY_AND_ARCH" 0 ((7647.05882 2639.51708) (7650.68156 2647.06572) (7650.82862 2688.53722)))
("SF_MASONRY_AND_ARCH" 0 ((7647.05882 1229.26188) (7665.91346 1229.26188)))
("SF_PLANTING" 0 ((7665.91346 369.53337) (7655.79842 380.84559) (7647.05882 414.78224)))
("SF_PLANTING" 0 ((7650.82862 429.86425) (7647.05882 426.09446) (7647.05882 414.78224)))
("SF_PLANTING" 0 ((7650.82862 6693.06210) (7669.68326 6700.60305)))
("SF_PLANTING" 0 ((7650.82862 6500.75407) (7650.82862 6481.90045)))
("SF_PLANTING" 0 ((7673.45305 6534.69106) (7668.48529 6519.60758) (7650.82862 6500.75407)))
("SF_PLANTING" 0 ((7669.68326 6474.35905) (7650.82862 6481.90045)))
("SF_MASONRY_AND_ARCH" 0 ((7714.93213 2726.24434) (7692.30769 2718.85034) (7653.91980 2719.07138) (7650.91290
2726.18009) (7650.82862 2775.26369)))
("SF_MASONRY_AND_ARCH" 0 ((7865.76075 2779.03495) (7809.19966 2779.18269) (7794.11765 2782.79231) (7775.26301
2779.04118) (7665.91346 2778.88722) (7650.82862 2775.26369)))
("SF_SOLAR" 0 ((7665.91346 8212.66968) (7673.46414 8209.05023) (7686.65158 8212.66968)))
("SF_PLANTING" 0 ((7673.45305 6711.91527) (7665.91346 6768.47636)))
("SF_PLANTING" 0 ((7665.91346 6768.47636) (7680.99548 6779.78857)))
("SF_PLANTING" 0 ((7673.45305 6534.69106) (7669.83100 6542.23891) (7669.53552 6583.71041) (7665.91346 6595.02262)))
("SF_PLANTING" 0 ((7669.68326 6659.12545) (7666.06052 6655.19977) (7665.91346 6595.02262)))
("SF_PLANTING" 0 ((7665.91346 6429.11018) (7669.68326 6421.56855)))
("SF_PLANTING" 0 ((7669.68326 6474.35905) (7665.91346 6429.11018)))
("SF_PLANTING" 0 ((7684.76527 279.03563) (7685.82240 305.42986) (7706.19943 343.13631) (7725.72794 415.46233)
(7707.38971 418.54514) (7696.22590 414.62692) (7683.87115 395.92760) (7679.79061 380.85045) (7665.91346 369.53337)))
("SF_PLANTING" 0 ((7669.68326 6930.61867) (7669.68326 6972.09627)))
("SF_PLANTING" 0 ((7688.53790 7009.80419) (7679.79061 6983.40882) (7669.68326 6972.09627)))
("SF_PLANTING" 0 ((7673.45305 6923.07692) (7669.68326 6930.61867)))
("SF_PLANTING" 0 ((7669.68326 6659.12545) (7669.68326 6700.60305)))
("SF_PLANTING" 0 ((7669.68326 6700.60305) (7673.45305 6711.91527)))
("SF_PLANTING" 0 ((7703.61991 6647.81324) (7669.68326 6659.12545)))
("SF_PLANTING" 0 ((7703.61991 6481.90045) (7669.68326 6474.35905)))
("SF_PLANTING" 0 ((7673.45305 6180.24140) (7669.68948 6217.94864) (7669.53484 6315.98801) (7662.15464 6338.61244)
(7669.52862 6365.00747) (7666.20894 6380.09050) (7669.68326 6421.56855)))
("SF_PLANTING" 0 ((7711.16233 6447.96380) (7703.46527 6422.77296) (7669.68326 6421.56855)))
("SF_MASONRY_AND_ARCH" 0 ((7669.68326 3046.75690) (7692.30769 3046.75690)))
("SF_PLANTING" 0 ((7673.45305 6923.07692) (7692.30769 6923.07692)))
("SF_PLANTING" 0 ((7673.45305 6711.91527) (7684.76527 6712.97206) (7707.38971 6725.94197) (7733.78676 6730.76923)))
("SF_PLANTING" 0 ((7673.45305 6534.69106) (7699.85011 6534.69106)))
("SF_PLANTING" 0 ((7711.16233 565.61086) (7677.22568 561.84106)))
("SF_PLANTING" 0 ((7684.76527 279.03563) (7677.22568 267.72342)))
("SF_SOLAR" 0 ((7680.99548 8223.98190) (7686.65158 8212.66968)))
("SF_PLANTING" 0 ((7680.99548 6779.78857) (7696.07749 6779.78857)))
("SF_MASONRY_AND_ARCH" 0 ((7865.76075 1229.26188) (7692.30769 1229.26674) (7680.99548 1233.03167)))
("SF_SOLAR" 0 ((7684.76527 7895.92760) (7718.70192 7895.92760)))
("SF_PLANTING" 0 ((7711.16233 279.03563) (7684.76527 279.03563)))
("SF_SOLAR" 0 ((7699.84921 8212.66968) (7696.01052 8212.66968) (7686.65158 8212.66968)))
("SF_SOLAR" 0 ((8706.63744 7846.90803) (7948.71889 7846.90803) (7934.69118 7861.99095) (7909.96086 7907.23982)
(7821.56278 8020.36199) (7774.21425 8092.00611) (7689.59627 8197.58993) (7686.65158 8212.66968)))
("SF_ARCHITECTURE" 0 ((7692.30769 7579.18552) (7688.54276 7564.10260) (7688.53790 7009.80419)))
("SF_PLANTING" 0 ((7688.53790 7009.80419) (7707.38971 7009.95204) (7718.70192 7014.48314) (7771.49321 7053.99661)
(7812.97229 7076.48631) (7828.05430 7080.09559) (7839.06346 7066.36527) (7834.53959 7055.05305) (7820.51188
7039.96957)))
("SF_ARCHITECTURE" 0 ((7692.30769 7639.51731) (7722.47455 7635.74661)))
("SF_ARCHITECTURE" 0 ((7692.30769 7639.51731) (7692.31391 7756.41018) (7696.07749 7767.72251)))
("SF_ARCHITECTURE" 0 ((7692.30769 7579.18552) (7707.38971 7579.18552)))
("SF_PLANTING" 0 ((7692.30769 6923.07692) (7703.47217 6896.68201) (7703.61991 6874.05758)))
("SF_PLANTING" 0 ((7699.85011 6926.84740) (7692.30769 6923.07692)))
("SF_MASONRY_AND_ARCH" 0 ((7692.30769 1546.00396) (7703.61991 1549.62602) (7775.26301 1549.92149) (7790.34785
1553.53869) (7865.76075 1549.77376)))
("SF_PLANTING" 0 ((7731.90045 6774.13247) (7703.62681 6772.40204) (7696.07749 6779.78857)))
("SF_PLANTING" 0 ((7714.93213 6817.49649) (7696.07749 6779.78857)))
("SF_PLANTING" 0 ((7696.07749 6346.15385) (7706.19253 6334.84163) (7718.70192 6297.13416)))
("SF_MASONRY_AND_ARCH" 0 ((7696.07749 2458.52161) (7696.07749 2500.00000)))
("SF_MASONRY_AND_ARCH" 0 ((7696.07749 2500.00000) (7714.93213 2507.39321) (7869.53337 2507.54174)))
("SF_MASONRY_AND_ARCH" 0 ((7730.01414 2401.96052) (7696.07749 2401.96052)))
("SF_SOLAR" 0 ((9977.37557 7911.01052) (9984.91109 7933.63495) (9981.15226 7960.03020) (9980.99830 8137.25498)
(9977.52330 8148.56719) (9977.22093 8197.58665) (9973.45045 8205.12161) (9962.29355 8212.51505) (9317.49717 8212.66312)
(9287.33032 8205.42432) (9181.75057 8212.66312) (9038.46154 8212.66312) (9019.60690 8208.90554) (9000.75509 8212.52172)
(8921.56957 8212.66312) (8895.17251 8208.89887) (8574.66063 8212.66312) (8521.86934 8205.28281) (8461.53846 8212.66312)
(8261.68835 8212.66312) (8239.06391 8208.89898) (8205.12726 8212.66312) (8152.33880 8208.90543) (8133.48416 8212.66968)
(8107.08993 8212.66968) (8092.00509 8212.66968) (7699.84921 8212.66968)))
("SF_SOLAR" 1 ((7699.84921 8212.66968) (7701.73450 8205.12817) (7699.84921 8203.24287) (7697.96380 8205.12817)))
("SF_PLANTING" 0 ((7699.85011 6926.84740) (7712.35260 6957.01357) (7741.47477 6997.44174) (7805.42986 7038.77206)
(7820.51188 7039.96957)))
("SF_PLANTING" 0 ((7818.62839 6938.15962) (7775.26301 6949.32398) (7730.01414 6931.66810) (7699.85011 6926.84740)))
("SF_PLANTING" 0 ((7703.61991 6481.90045) (7699.85011 6534.69106)))
("SF_PLANTING" 0 ((7703.61991 6647.81324) (7711.00701 6595.02262) (7703.76765 6572.39819) (7703.47217 6542.23891)
(7699.85011 6534.69106)))
("SF_SOLAR" 0 ((7703.61991 8122.17195) (7716.18948 8107.08891)))
("SF_PLANTING" 0 ((7801.66007 6843.89140) (7782.80543 6848.86618) (7748.86878 6869.23688) (7703.61991 6874.05758)))
("SF_PLANTING" 0 ((7703.61991 6858.97410) (7703.61991 6874.05758)))
("SF_PLANTING" 0 ((7703.61991 6858.97410) (7714.93213 6817.49649)))
("SF_PLANTING" 0 ((7703.61991 6647.81324) (7711.16233 6647.81324)))
("SF_PLANTING" 0 ((7703.61991 6481.90045) (7790.34785 6481.89389) (7805.42986 6478.42579) (7816.74208 6481.90045)))
("SF_ARCHITECTURE" 0 ((7707.38971 7579.18552) (7722.47455 7571.79208) (7763.95079 7569.07104) (8951.73450 7571.64400)))
("SF_ARCHITECTURE" 0 ((7707.38971 7579.18552) (7721.41742 7609.35147) (7722.47455 7635.74661)))
("SF_MASONRY_AND_ARCH" 0 ((7707.38971 2175.71618) (7711.16233 2149.32127)))
("SF_MASONRY_AND_ARCH" 0 ((7707.38971 2175.71618) (7737.55656 2189.74943) (7779.03563 2194.57014)))
("SF_PLANTING" 0 ((7869.53337 825.79186) (7854.44853 814.63428) (7726.24434 814.48586) (7707.38971 818.24943)))
("SF_PLANTING" 0 ((7711.16233 6647.81324) (7711.16233 6659.12545)))
("SF_PLANTING" 0 ((7711.16233 6647.81324) (7756.41120 6636.50102)))
("SF_PLANTING" 0 ((7711.16233 279.03563) (7715.98846 260.18790) (7726.24434 252.63857)))
("SF_PLANTING" 0 ((7711.16233 279.03563) (7737.55656 316.74208)))
("SF_PLANTING" 0 ((7731.90045 6774.13247) (7732.58190 6806.17771) (7714.93213 6817.49649)))
("SF_MASONRY_AND_ARCH" 0 ((7865.76075 1338.61143) (7854.44853 1334.84785) (7714.93213 1331.07093)))
("SF_MASONRY_AND_ARCH" 0 ((7722.47455 1300.90498) (7714.93213 1300.90498)))
("SF_ARCHITECTURE" 0 ((8951.73450 7635.74661) (7722.47455 7635.74661)))
("SF_SOLAR" 0 ((7726.24434 7873.30317) (7733.78676 7877.07387)))
("SF_PLANTING" 0 ((7726.24434 252.63857) (7726.24434 241.32636)))
("SF_PLANTING" 0 ((7812.97229 316.74208) (7786.57523 300.60916) (7726.24434 252.63857)))
("SF_PLANTING" 0 ((7726.24434 241.32636) (7748.86878 230.16256) (7835.59672 228.81075) (7850.52410 211.16233)
(7846.90894 184.76527)))
("SF_PLANTING" 0 ((7731.90045 6774.13247) (7733.78676 6730.76923)))
("SF_PLANTING" 0 ((7731.90045 6774.13247) (7763.95079 6775.86980) (7782.80543 6768.47636)))
("SF_SOLAR" 0 ((7741.32636 8193.81606) (7733.78676 8197.58665)))
("SF_PLANTING" 0 ((7752.63857 6723.22749) (7733.78676 6730.76923)))
("SF_MASONRY_AND_ARCH" 0 ((7865.76075 3042.98643) (7733.78676 3042.98643)))
("SF_PLANTING" 0 ((7745.09898 471.34333) (7733.78676 448.71889)))
("SF_SOLAR" 0 ((7797.88744 7846.90803) (7737.55656 7843.13722)))
("SF_PLANTING" 0 ((7763.95079 316.74208) (7756.40362 313.12557) (7737.55656 316.74208)))
("SF_PLANTING" 0 ((7801.66007 388.38518) (7797.73416 380.98643) (7745.25226 335.59672) (7737.55656 316.74208)))
("SF_MASONRY_AND_ARCH" 0 ((7752.63857 1828.80871) (7741.32636 1847.66188)))
("SF_MASONRY_AND_ARCH" 0 ((7748.86878 1813.72455) (7741.32636 1809.95475)))
("SF_SOLAR" 0 ((7745.09898 8152.33778) (7756.41120 8167.42081)))
("SF_MASONRY_AND_ARCH" 0 ((7745.09898 2398.19005) (7756.41120 2401.95430) (7861.99095 2401.96052)))
("SF_PLANTING" 0 ((7812.97229 641.02658) (7797.88744 644.64864) (7745.09898 644.79638)))
("SF_SOLAR" 0 ((7748.86878 8178.73303) (7756.41120 8167.42081)))
("SF_MASONRY_AND_ARCH" 0 ((7752.63857 1806.18495) (7748.86878 1813.72455)))
("SF_MASONRY_AND_ARCH" 0 ((7752.63857 1828.80871) (7748.86878 1813.72455)))
("SF_PLANTING" 0 ((7752.63857 6723.22749) (7756.41120 6636.50102)))
("SF_PLANTING" 0 ((7752.63857 6723.22749) (7760.18790 6729.57149) (7779.03563 6734.53971)))
("SF_MASONRY_AND_ARCH" 0 ((7752.63857 1828.80871) (7775.26301 1828.80871)))
("SF_MASONRY_AND_ARCH" 0 ((7869.53337 1760.93609) (7858.22115 1753.54830) (7760.18790 1749.47545) (7752.63857
1745.85124)))
("SF_SOLAR" 0 ((7756.41120 8167.42081) (7779.03563 8159.87941)))
("SF_PLANTING" 0 ((7794.11765 6583.71041) (7771.49943 6588.68518) (7765.00792 6595.02919) (7756.55826 6617.64706)
(7756.41120 6636.50102)))
("SF_PLANTING" 0 ((7790.34785 6651.58371) (7775.26301 6637.55701) (7756.41120 6636.50102)))
("SF_MASONRY_AND_ARCH" 0 ((7775.26301 2288.83835) (7774.96131 2277.52613) (7763.95079 2266.21391)))
("SF_MASONRY_AND_ARCH" 0 ((7763.95079 1953.24310) (7794.11765 1949.47183) (7854.44367 1949.61957) (7861.99095
1953.24310)))
("SF_PLANTING" 0 ((7771.49321 573.15328) (7771.49321 565.61086) (7763.95079 561.84106)))
("SF_ARCHITECTURE" 0 ((9724.73699 7635.74661) (9822.40633 7636.95090) (9822.62104 7771.49321) (9815.22715 7781.60113)
(7771.49321 7779.03473)))
("SF_SOLAR" 0 ((7779.03563 8159.87941) (7808.00939 8114.63054) (7812.97229 8099.54751)))
("SF_SOLAR" 0 ((7960.03111 8163.65000) (7794.11765 8163.64344) (7779.03563 8159.87941)))
("SF_SOLAR" 0 ((7779.03563 8129.71335) (7786.57523 8125.94276)))
("SF_PLANTING" 0 ((7779.03563 6734.53971) (7786.58281 6730.91753) (7828.05430 6730.76923)))
("SF_PLANTING" 0 ((7782.80543 6768.47636) (7782.65769 6742.08801) (7779.03563 6734.53971)))
("SF_PLANTING" 0 ((7779.03563 6542.23201) (7786.57523 6546.00328)))
("SF_MASONRY_AND_ARCH" 0 ((7779.03563 2194.57014) (7779.03563 2239.81900)))
("SF_MASONRY_AND_ARCH" 0 ((7869.53337 2190.79966) (7861.98405 2194.42240) (7779.03563 2194.57014)))
("SF_SOLAR" 0 ((7782.80543 7971.34231) (7789.14921 7993.96674) (7782.80543 8012.82059)))
("SF_PLANTING" 0 ((7782.80543 6768.47636) (7797.88258 6769.68066) (7805.42986 6779.78857)))
("SF_PLANTING" 0 ((7816.74208 6523.37885) (7794.12455 6535.74050) (7786.57523 6546.00328)))
("SF_PLANTING" 0 ((7794.11765 6583.71041) (7793.96301 6561.08597) (7786.57523 6546.00328)))
("SF_MASONRY_AND_ARCH" 0 ((7786.57523 2846.90826) (7794.26606 2831.97941) (7801.66007 2828.20894) (7858.22115
2828.20894) (7869.53337 2831.82477)))
("SF_PLANTING" 0 ((7794.11765 6583.71041) (7805.42986 6593.82489) (7820.51188 6598.49050) (7834.24344 6587.48744)
(7831.82410 6579.93993)))
("SF_SOLAR" 0 ((7797.88744 8182.50385) (7797.88744 8174.96222)))
("SF_SOLAR" 0 ((7797.88744 8088.23529) (7812.97229 8099.54751)))
("SF_SOLAR" 0 ((7797.88744 7846.90803) (7835.59672 7843.13722) (7907.23982 7843.28529) (7933.63405 7846.90803)))
("SF_SOLAR" 0 ((7797.88744 7846.90803) (7805.28213 7880.84468) (7809.34808 7944.94717) (7831.82410 7990.19615)))
("SF_PLANTING" 0 ((7797.88744 6802.41301) (7805.42986 6779.78857)))
("SF_MASONRY_AND_ARCH" 0 ((7797.88744 1828.80871) (7854.44853 1828.95645) (7865.76075 1832.57919)))
("SF_PLANTING" 0 ((7892.15781 6843.89140) (7880.84559 6833.78348) (7812.97229 6836.50452) (7801.66007 6843.89140)))
("SF_PLANTING" 0 ((7801.66007 6843.89140) (7814.02794 6874.05758) (7831.82410 6889.14027)))
("SF_SOLAR" 0 ((7967.57070 8148.56719) (7956.25848 8141.18020) (7805.42986 8141.02557)))
("SF_PLANTING" 0 ((7805.42986 6779.78857) (7892.15781 6783.55984)))
("SF_SOLAR" 0 ((7820.51188 8095.77670) (7812.97229 8099.54751)))
("SF_PLANTING" 0 ((7816.74208 6523.37885) (7816.74208 6481.90045)))
("SF_PLANTING" 0 ((7816.74208 6523.37885) (7839.36652 6542.23201)))
("SF_PLANTING" 0 ((7944.94627 6474.35905) (7929.86425 6481.75238) (7816.74208 6481.90045)))
("SF_PLANTING" 0 ((7818.62839 6938.15962) (7817.79842 6911.76471) (7831.82410 6889.14027)))
("SF_PLANTING" 0 ((7818.62839 6938.15962) (7824.13609 6957.01357) (7828.04186 7013.57466) (7820.51188 7039.96957)))
("SF_PLANTING" 0 ((7818.62839 6938.15962) (7869.53337 6941.92432) (7895.92760 6938.15962)))
("SF_SOLAR" 0 ((8042.98643 8054.29864) (8027.90441 8061.83348) (7967.57070 8061.69208) (7956.25848 8058.22398)
(7937.40667 8061.83348) (7850.67873 8060.32342) (7828.20271 8080.69389) (7820.51188 8095.77670)))
("SF_SOLAR" 0 ((7820.51188 8095.77670) (7861.99095 8103.17025) (7993.96776 8103.31833)))
("SF_MASONRY_AND_ARCH" 0 ((7824.28450 2582.95600) (7820.51188 2567.87330)))
("SF_PLANTING" 0 ((7820.51188 561.84106) (7828.06120 565.46312) (7858.22115 565.61086)))
("SF_MASONRY_AND_ARCH" 0 ((7861.99095 2586.72726) (7824.28450 2582.95600)))
("SF_PLANTING" 0 ((7978.88292 6723.22749) (7963.80090 6730.62093) (7948.71889 6730.62093) (7933.63405 6725.33360)
(7911.00962 6730.62093) (7828.05430 6730.76923)))
("SF_PLANTING" 0 ((7843.13631 6666.66640) (7828.20204 6711.91527) (7828.05430 6730.76923)))
("SF_PLANTING" 0 ((7861.99095 6885.36980) (7831.82410 6889.14027)))
("SF_SOLAR" 0 ((7839.36652 7873.30317) (7869.53337 7873.30317)))
("SF_SOLAR" 0 ((7850.67873 7922.32274) (7843.13631 7941.17647)))
("SF_SOLAR" 0 ((7850.67873 7922.32274) (7847.05600 7914.77466) (7846.90894 7880.84468)))
("SF_MASONRY_AND_ARCH" 0 ((7846.90894 957.76867) (7858.22115 957.76867) (7861.99095 953.99604)))
("SF_ARCHITECTURE" 0 ((7846.90894 -3.77070) (7846.90894 184.76527)))
("SF_ARCHITECTURE" 0 ((7846.90894 -3.77070) (7865.76075 -3.77070) (7914.78224 -3.77070)))
("SF_SOLAR" 0 ((7850.67873 8050.52783) (7869.53337 8027.90339)))
("SF_SOLAR" 0 ((7850.67873 7922.32274) (7865.76075 7899.69830)))
("SF_PLANTING" 0 ((7865.76075 6968.32579) (7854.44853 6964.55532)))
("SF_SOLAR" 0 ((7865.76075 8005.27896) (7858.22115 8001.50837)))
("SF_SOLAR" 0 ((7861.99095 8118.40113) (7869.53337 8133.48416)))
("SF_PLANTING" 0 ((7892.15781 6843.89140) (7884.46075 6858.97410) (7866.81787 6874.20509) (7861.99095 6885.36980)))
("SF_PLANTING" 0 ((7861.99095 6885.36980) (7873.30317 6895.48428) (7899.69740 6904.22296)))
("SF_SOLAR" 0 ((7865.76075 8084.46448) (7869.53337 8073.15226)))
("SF_SOLAR" 0 ((8137.25396 7911.01052) (8108.13869 7944.94717) (8068.33190 8009.04977) (8050.52885 8026.69910)
(7869.53337 8027.90339)))
("SF_SOLAR" 0 ((7895.92760 7990.19615) (7870.73676 8016.59118) (7869.53337 8027.90339)))
("SF_SOLAR" 0 ((7877.07296 7990.19615) (7869.53337 7986.42534)))
("SF_SOLAR" 0 ((7888.38518 8050.52783) (7892.15781 8039.21561)))
("SF_SOLAR" 0 ((7899.69740 7960.03020) (7888.38518 7956.25939)))
("SF_PLANTING" 0 ((7888.38518 6806.18428) (7892.15781 6783.55984)))
("SF_PLANTING" 0 ((7892.15781 6843.89140) (7944.94627 6844.03971) (7956.25848 6847.66188)))
("SF_PLANTING" 0 ((7918.55204 6776.01810) (7892.15781 6783.55984)))
("SF_SOLAR" 0 ((7899.69740 8125.94276) (7895.92760 8118.40113)))
("SF_SOLAR" 0 ((7895.92760 7990.19615) (7911.15803 7963.80090) (7929.86425 7948.87262) (8095.77771 7948.71799)))
("SF_SOLAR" 0 ((7895.92760 7990.19615) (7911.00962 7993.96018) (8069.38066 7993.96674)))
("SF_PLANTING" 0 ((7895.92760 6938.15962) (7899.69740 6919.30645)))
("SF_PLANTING" 0 ((7895.92760 6938.15962) (7903.61708 6952.04536) (7926.09446 6959.73462) (7956.25848 6960.63620)
(7967.57070 6957.01357)))
("SF_PLANTING" 0 ((7941.17647 6919.30645) (7899.69740 6919.30645)))
("SF_PLANTING" 0 ((7899.69740 6904.22296) (7899.69740 6919.30645)))
("SF_PLANTING" 0 ((7899.69740 6904.22296) (7937.39910 6881.44446) (7949.90916 6859.12896) (7956.25848 6855.20362)))
("SF_SOLAR" 0 ((7914.78224 8046.75724) (7911.00962 8039.21561)))
("SF_SOLAR" 0 ((7914.78224 8005.27896) (7911.00962 8012.82059)))
("SF_ARCHITECTURE" 0 ((9543.74152 -3.77070) (9521.11708 -3.77070) (7929.86425 -3.77070) (7914.78224 -3.77070)))
("SF_ARCHITECTURE" 0 ((7918.55204 64.10260) (7914.92930 56.55419) (7914.78224 -3.77070)))
("SF_SOLAR" 0 ((7918.55204 7911.01052) (8054.29864 7911.00396) (8129.70679 7907.38790) (8137.25396 7911.01052)))
("SF_PLANTING" 0 ((7918.55204 6776.01810) (7922.32183 6757.16414)))
("SF_PLANTING" 0 ((7918.55204 6776.01810) (7975.11312 6787.03450) (8020.36199 6779.78857)))
("SF_ARCHITECTURE" 0 ((9539.96889 124.43439) (7918.55204 124.43439)))
("SF_ARCHITECTURE" 0 ((7918.55204 64.10260) (7914.78224 79.18552) (7914.92930 113.12217) (7918.55204 124.43439)))
("SF_ARCHITECTURE" 0 ((7918.55204 124.43439) (7918.69977 184.61199) (7922.32183 188.53790)))
("SF_ARCHITECTURE" 0 ((7918.55204 64.10260) (7978.88292 64.10260) (7993.96776 64.10260) (8344.64649 64.10260)
(8363.49830 64.10260) (8476.62048 64.10260) (8499.24491 64.10260) (9543.74152 67.87330)))
("SF_SOLAR" 0 ((7922.32183 8114.63054) (7922.32183 8125.94276)))
("SF_SOLAR" 0 ((7922.32183 8084.46448) (7922.32183 8076.92308)))
("SF_ARCHITECTURE" 0 ((7978.88292 188.53790) (7963.80090 184.76527) (7929.87115 184.91369) (7922.32183 188.53790)))
("SF_ARCHITECTURE" 0 ((7926.09446 2092.76018) (7922.32873 2070.13575) (7926.08756 2039.96957) (7926.08756 1836.34966)
(7922.32873 1817.49717) (7926.09446 1598.79242) (7922.32873 1576.16799) (7922.32183 1014.32975) (7926.09446 976.62048)
(7922.32873 953.99604) (7922.32183 188.53790)))
("SF_ARCHITECTURE" 0 ((7926.09355 2820.51256) (7926.09446 2707.39038)))
("SF_ARCHITECTURE" 0 ((7926.09355 2820.51256) (7926.09446 3585.97285)))
("SF_ARCHITECTURE" 0 ((7926.09355 2820.51256) (8668.92817 2820.51878) (8691.55260 2824.28382) (8755.65611 2824.13609)
(8770.73812 2820.51878) (8989.44287 2824.28382) (9012.06731 2820.51878) (9539.96889 2820.51256)))
("SF_SOLAR" 0 ((7948.71889 7960.03020) (7941.16957 7970.13812) (7926.09446 7971.34231)))
("SF_SOLAR" 0 ((7926.09446 7941.17647) (7937.40667 7922.32274)))
("SF_ARCHITECTURE" 0 ((7926.09446 3585.97285) (7948.71889 3587.17704) (7958.82624 3597.28507) (7961.07986 3650.07545)
(7986.42534 3710.40724)))
("SF_ARCHITECTURE" 0 ((7926.09446 2707.39038) (9539.96889 2707.39038)))
("SF_ARCHITECTURE" 0 ((7926.09446 2707.39038) (7926.08756 2138.00905) (7922.32183 2115.38462) (7926.09446 2092.76018)))
("SF_ARCHITECTURE" 0 ((8650.07636 2413.27274) (8642.52704 2409.65000) (8552.03620 2405.58405) (8495.47511 2393.36312)
(8382.35294 2359.43337) (8295.62500 2325.49672) (8223.98190 2291.41855) (8133.48416 2238.76267) (8069.38066 2194.42240)
(7948.71889 2097.58710) (7926.09446 2092.76018)))
("SF_SOLAR" 0 ((7944.94627 8133.48416) (7956.25848 8118.40113)))
("SF_PLANTING" 0 ((7948.71889 6195.32421) (7948.71199 6432.88077) (7944.94627 6474.35905)))
("SF_PLANTING" 0 ((7944.94627 6474.35905) (7971.34333 6479.33405) (7981.45068 6489.44219) (7982.65554 6557.31550)))
("SF_ARCHITECTURE" 0 ((7944.94627 3797.13382) (7960.03111 3793.51176) (8009.04977 3793.20894) (8019.15713 3785.81538)
(8019.15713 3725.63846) (7986.42534 3710.40724)))
("SF_ARCHITECTURE" 0 ((7948.71799 5607.08857) (7948.71799 5588.23529) (7948.71799 5554.29864) (7948.71799 5471.34197)
(7948.71799 5448.71753) (7944.94627 3797.13382)))
("SF_ARCHITECTURE" 0 ((9539.96889 5607.08857) (7948.71799 5607.08857)))
("SF_ARCHITECTURE" 0 ((7948.71889 5750.37715) (7944.94627 5731.52330) (7948.42195 5690.04525) (7945.09468 5678.73303)
(7948.71799 5622.17195) (7948.71799 5607.08857)))
("SF_ARCHITECTURE" 0 ((7948.71889 6195.32421) (9536.19910 6195.32421)))
("SF_ARCHITECTURE" 0 ((7948.71889 6195.32421) (7948.71889 5829.56267)))
("SF_ARCHITECTURE" 0 ((7948.71889 5750.37715) (7944.94627 5769.23077) (7945.09468 5818.25011) (7948.71889 5829.56267)))
("SF_ARCHITECTURE" 0 ((9539.96889 5829.56267) (9513.57466 5833.33326) (9483.40781 5829.56923) (8050.52885 5829.56923)
(8031.67421 5833.32014) (8016.59219 5829.71086) (7948.71889 5829.56267)))
("SF_ARCHITECTURE" 0 ((7948.71889 5750.37715) (9539.96889 5750.37715)))
("SF_PLANTING" 0 ((7956.25848 6847.66188) (7956.25848 6855.20362)))
("SF_PLANTING" 0 ((7975.11312 6862.74536) (7956.25848 6855.20362)))
("SF_PLANTING" 0 ((7956.25848 6847.66188) (7975.11312 6836.49796) (8076.92308 6832.57919)))
("SF_SOLAR" 0 ((7960.03111 8163.65000) (7967.57070 8148.56719)))
("SF_SOLAR" 0 ((7960.03111 8163.65000) (7982.65554 8174.66606) (8009.04977 8159.87941)))
("SF_SOLAR" 0 ((7967.57070 8197.58665) (7967.57070 8186.27443) (7963.80090 8182.50385)))
("SF_SOLAR" 0 ((7967.57070 8039.21561) (7963.80090 8046.75724)))
("SF_SOLAR" 0 ((7986.42534 8137.25498) (7967.57070 8148.56719)))
("SF_SOLAR" 0 ((7967.57070 8076.92308) (7967.57070 8069.38167)))
("SF_SOLAR" 0 ((8054.29864 7971.34231) (7975.12002 7971.49706) (7968.77557 7975.26109) (7967.57070 7982.65452)))
("SF_SOLAR" 0 ((7967.57070 7877.07387) (7971.34333 7858.22025)))
("SF_PLANTING" 0 ((7993.96776 6892.91075) (7978.88292 6898.34661) (7967.57070 6896.68201)))
("SF_PLANTING" 0 ((7978.88292 6723.22749) (7978.88982 6602.56437) (7982.65554 6557.31550)))
("SF_PLANTING" 0 ((7978.88292 6723.22749) (8012.66629 6742.08801) (8020.36199 6779.78857)))
("SF_ARCHITECTURE" 0 ((7978.88292 3717.94876) (7986.42534 3710.40724)))
("SF_ARCHITECTURE" 0 ((7978.88292 188.53790) (8001.50735 184.76527) (8035.43914 184.91369) (8046.75713 188.53790)))
("SF_ARCHITECTURE" 0 ((7978.88292 188.53790) (7978.88982 2051.28179) (7990.34355 2077.52896) (8020.36199 2100.30192)))
("SF_SOLAR" 0 ((7982.65554 7877.07387) (8005.27998 7877.07387)))
("SF_ARCHITECTURE" 0 ((8951.73450 6561.08597) (8940.42138 6557.32206) (8789.59276 6557.16719) (8774.51561 6549.62545)
(8767.12296 6538.46154) (8766.81369 6402.72149) (8763.04321 6396.37771) (8623.67930 6395.18009) (8612.52240 6399.09876)
(8608.60419 6410.25633) (8608.44887 6542.23201) (8603.77036 6553.38982) (8597.27885 6557.16063) (7982.65554
6557.31550)))
("SF_SOLAR" 0 ((7993.96776 8118.40113) (7986.42534 8137.25498)))
("SF_SOLAR" 0 ((7986.42534 8137.25498) (7997.73133 8144.49367) (8005.27998 8141.02557)))
("SF_SOLAR" 0 ((7990.19514 8073.15226) (7990.19514 8080.69389)))
("SF_ARCHITECTURE" 0 ((7997.73756 5690.04525) (9479.63801 5690.03869) (9494.72002 5686.27443)))
("SF_SOLAR" 0 ((8020.36199 8095.77670) (8005.27998 8103.31833)))
("SF_SOLAR" 0 ((8009.04977 8159.87941) (8010.25464 8152.33122) (8024.13179 8137.25498)))
("SF_SOLAR" 0 ((8246.60633 8163.65000) (8020.36199 8163.64344) (8009.04977 8159.87941)))
("SF_SOLAR" 0 ((8009.04977 8039.21561) (8009.04977 8046.75724)))
("SF_SOLAR" 0 ((8012.81957 8012.82059) (8012.81957 8005.27896)))
("SF_ARCHITECTURE" 0 ((8016.59219 6440.42240) (8042.98643 6444.18643) (8540.72398 6444.19299)))
("SF_SOLAR" 0 ((8020.36199 8095.77670) (8021.55995 8080.70045) (8027.90441 8073.15226)))
("SF_SOLAR" 0 ((8020.36199 8095.77670) (8031.67421 8103.31833)))
("SF_PLANTING" 0 ((8076.92308 6832.57919) (8065.45622 6787.47862) (8050.52885 6779.93688) (8020.36199 6779.78857)))
("SF_ARCHITECTURE" 0 ((8020.36199 2100.30192) (8035.44400 2092.76018)))
("SF_ARCHITECTURE" 0 ((8035.44400 2111.61414) (8020.36199 2100.30192)))
("SF_SOLAR" 0 ((8061.84106 8084.46448) (8024.13179 8137.25498)))
("SF_SOLAR" 0 ((8250.37613 8144.79638) (8239.06391 8141.03213) (8174.96324 8141.17364) (8152.33880 8144.78982)
(8133.48416 8141.03213) (8031.68111 8140.87760) (8024.13179 8137.25498)))
("SF_ARCHITECTURE" 0 ((8024.13179 6489.44186) (8092.00509 6489.29367) (8110.85973 6485.67127) (8186.27545 6485.81946)
(8201.35747 6489.43529) (8521.86934 6489.29367) (8536.94661 6484.47342) (8543.29038 6478.12308) (8544.34672 6451.74118)
(8540.72398 6444.19299)))
("SF_SOLAR" 0 ((8027.90441 8182.50385) (8027.90441 8174.96222)))
("SF_SOLAR" 0 ((8035.44400 8005.27896) (8031.67421 8012.82059)))
("SF_ARCHITECTURE" 0 ((8050.52885 2104.07240) (8042.98643 2104.07240) (8035.44400 2111.61414)))
("SF_ARCHITECTURE" 0 ((8035.44400 2111.61414) (8050.52885 2122.92636)))
("SF_SOLAR" 0 ((8050.52885 8035.44502) (8042.98643 8054.29864)))
("SF_SOLAR" 0 ((8042.98643 8054.29864) (8050.53371 8060.49446) (8069.38066 8061.84005)))
("SF_SOLAR" 0 ((8046.75622 8076.92308) (8054.29864 8076.92308)))
("SF_ARCHITECTURE" 0 ((8118.40215 241.32636) (8088.23529 233.94005) (8046.75713 237.55656)))
("SF_ARCHITECTURE" 0 ((8046.75713 188.53790) (8046.75713 226.24434) (8046.75713 237.55656)))
("SF_ARCHITECTURE" 0 ((8046.75713 237.55656) (8046.91154 2006.03292) (8058.06844 2019.91844) (8076.92308 2026.07794)
(8174.96324 2091.56912) (8299.39762 2157.75781) (8412.51980 2201.06233) (8469.08088 2217.19457)))
("SF_ARCHITECTURE" 0 ((8046.75713 188.53790) (8061.84106 184.76527) (9377.82805 184.77217) (9392.91097 188.53790)))
("SF_ARCHITECTURE" 0 ((8069.38066 2115.38462) (8058.07602 2116.58258) (8050.52885 2122.92636)))
("SF_ARCHITECTURE" 0 ((8080.69287 2145.55079) (8058.07602 2133.18903) (8050.52885 2122.92636)))
("SF_SOLAR" 0 ((8054.29864 7971.34231) (8058.06844 7978.88394) (8054.29864 7982.65452)))
("SF_SOLAR" 0 ((8054.29864 7971.34231) (8058.06844 7960.03020)))
("SF_SOLAR" 0 ((8054.29864 7869.53247) (8061.84106 7858.22025)))
("SF_PLANTING" 0 ((8076.92308 6832.57919) (8072.09615 6855.20362) (8058.06844 6866.51584)))
("SF_SOLAR" 0 ((8061.84106 8107.08891) (8088.23529 8099.69548) (8137.25396 8099.39955) (8152.33880 8095.77670)))
("SF_SOLAR" 0 ((8069.38066 8061.84005) (8061.84106 8084.46448)))
("SF_SOLAR" 0 ((8084.46550 8092.00611) (8061.84106 8084.46448)))
("SF_SOLAR" 0 ((8073.15328 8118.40113) (8069.38066 8125.94276)))
("SF_SOLAR" 0 ((8069.38066 8061.84005) (8088.23529 8058.06946) (8152.33880 8061.84005) (8223.98190 8061.69208)
(8242.83654 8058.07602) (8291.85520 8061.69197) (8306.79016 8054.15057) (8318.24943 8031.67421)))
("SF_SOLAR" 0 ((8080.69287 8050.52783) (8085.52115 8039.21561) (8103.31731 8020.36199)))
("SF_ARCHITECTURE" 0 ((8080.69287 2145.55079) (8088.23529 2138.00905)))
("SF_ARCHITECTURE" 0 ((8080.69287 2145.55079) (8174.96324 2208.46188) (8276.77319 2261.53552) (8337.10407 2287.64118)
(8487.93269 2337.71075) (8634.99152 2364.10566) (8657.61595 2364.25339)))
("SF_SOLAR" 0 ((8084.46550 8009.04977) (8088.23529 8016.59118)))
("SF_SOLAR" 0 ((8088.23529 7895.92760) (8095.77771 7858.22025)))
("SF_SOLAR" 0 ((8103.31731 8069.38167) (8099.54751 8080.69389)))
("SF_SOLAR" 0 ((8103.31731 8118.40113) (8103.31731 8129.71335)))
("SF_SOLAR" 0 ((8393.66516 7948.71799) (8363.49830 7952.33405) (8344.64649 7948.72455) (8148.56618 7948.87262)
(8138.31109 7956.26606) (8108.14559 8005.27896) (8103.31731 8020.36199)))
("SF_SOLAR" 0 ((8318.24943 8031.67421) (8306.93722 8027.90995) (8159.87839 8027.75543) (8110.86663 8023.98473)
(8103.31731 8020.36199)))
("SF_SOLAR" 0 ((8110.85973 7978.88394) (8107.08993 7971.34231)))
("SF_SOLAR" 0 ((8118.40215 8039.21561) (8118.40215 8046.75724)))
("SF_ARCHITECTURE" 0 ((8118.40215 241.32636) (8137.25396 237.55656) (8710.40724 237.56278) (8721.71946 241.32636)))
("SF_ARCHITECTURE" 0 ((8122.17195 361.99095) (8118.40701 350.67873) (8118.40215 241.32636)))
("SF_ARCHITECTURE" 0 ((8122.17195 1987.17975) (8141.02658 1987.17975)))
("SF_ARCHITECTURE" 0 ((8122.17195 935.14333) (8118.54921 927.59491) (8118.54921 874.81052) (8122.02421 863.49830)
(8122.32658 818.24943) (8129.71437 806.93722)))
("SF_ARCHITECTURE" 0 ((8122.17195 361.99095) (8144.79638 361.99095)))
("SF_ARCHITECTURE" 0 ((8122.17195 361.99095) (8122.32658 384.60848) (8129.71437 392.15781)))
("SF_SOLAR" 0 ((8125.94174 8182.50385) (8125.94174 8174.96222)))
("SF_SOLAR" 0 ((8125.94174 8084.46448) (8125.94174 8076.92308)))
("SF_SOLAR" 0 ((8129.71437 7858.22025) (8125.94174 7895.92760)))
("SF_ARCHITECTURE" 0 ((8144.79638 999.24491) (8137.24910 992.90249) (8125.94174 991.70532)))
("SF_SOLAR" 0 ((8137.25396 7944.94717) (8129.71437 7937.40577)))
("SF_ARCHITECTURE" 0 ((8129.71437 392.15781) (8129.71437 806.93722)))
("SF_ARCHITECTURE" 0 ((8646.30464 886.12274) (8642.52704 897.28167) (8631.22172 901.20667) (8163.65102 901.20667)
(8146.00124 886.12274) (8144.64174 825.79186) (8129.71437 806.93722)))
("SF_ARCHITECTURE" 0 ((8129.71437 392.15781) (8143.59152 380.84559) (8144.79638 361.99095)))
("SF_SOLAR" 0 ((8133.48416 8133.48416) (8163.65588 8096.98100) (8197.58767 8095.77670)))
("SF_SOLAR" 0 ((8348.41629 7986.42534) (8329.56165 7993.96018) (8133.48416 7993.96674)))
("SF_SOLAR" 0 ((8665.15837 7854.44943) (8641.47760 7899.55023) (8616.13971 7910.86244) (8137.25396 7911.01052)))
("SF_SOLAR" 0 ((8141.02658 8012.82059) (8141.02658 8001.50837)))
("SF_ARCHITECTURE" 0 ((8144.79638 1983.40848) (8141.02658 1983.40848) (8141.02658 1987.17975)))
("SF_ARCHITECTURE" 0 ((8163.65102 2009.80419) (8152.48586 2005.87828) (8141.02658 1987.17975)))
("SF_ARCHITECTURE" 0 ((8144.79638 999.24491) (8141.02568 1021.86934) (8141.03145 1968.32579) (8144.79638 1983.40848)))
("SF_ARCHITECTURE" 0 ((8171.19061 1998.49197) (8163.64344 1988.37760) (8144.79638 1983.40848)))
("SF_ARCHITECTURE" 0 ((8144.79638 999.24491) (8646.30373 999.25249) (8660.18371 1006.79423) (8661.38857 2149.32127)))
("SF_ARCHITECTURE" 0 ((8623.67930 346.90894) (8159.87839 346.91516) (8149.62330 350.83337) (8144.79638 361.99095)))
("SF_SOLAR" 0 ((8148.56618 8035.44502) (8148.56618 8046.75724)))
("SF_SOLAR" 0 ((8159.87839 8182.50385) (8159.87839 8174.96222)))
("SF_SOLAR" 0 ((8159.87839 7982.65452) (8171.19061 7967.57172)))
("SF_ARCHITECTURE" 0 ((8163.65102 2009.80419) (8171.19061 1998.49197)))
("SF_ARCHITECTURE" 0 ((8163.65102 2009.80419) (8190.04525 2031.37217) (8235.29412 2055.05305)))
("SF_ARCHITECTURE" 0 ((8167.42081 935.14333) (8178.73303 942.67896) (8627.45192 942.68382)))
("SF_SOLAR" 0 ((8171.19061 7960.03020) (8171.19061 7967.57172)))
("SF_SOLAR" 0 ((8190.04525 7971.34231) (8171.19061 7967.57172)))
("SF_ARCHITECTURE" 0 ((8171.19061 1998.49197) (8182.50283 1999.68982) (8242.68122 2037.24853) (8246.60633 2043.74084)))
("SF_SOLAR" 0 ((8269.23077 8099.54751) (8254.14876 8103.31176) (8220.21210 8099.84367) (8201.35747 8104.52251)
(8186.42251 8118.40113) (8178.73303 8133.48416)))
("SF_SOLAR" 0 ((8190.04525 8069.38167) (8190.04525 8080.69389)))
("SF_SOLAR" 0 ((8190.04525 8012.82059) (8190.04525 8001.50837)))
("SF_SOLAR" 0 ((8201.35747 7967.57172) (8197.58767 7982.65452)))
("SF_SOLAR" 0 ((8216.43948 8133.48416) (8216.43948 8122.17195)))
("SF_ARCHITECTURE" 0 ((8318.24943 3276.77251) (8288.08541 3273.00124) (8223.98880 3273.14898) (8216.44038 3276.77251)))
("SF_ARCHITECTURE" 0 ((8227.75170 3220.21143) (8201.50588 3221.41550) (8193.96346 3235.29412) (8195.01991 3261.68903)
(8216.44038 3276.77251)))
("SF_ARCHITECTURE" 0 ((9291.10011 3273.00124) (9294.87183 4377.82805) (9294.87183 4400.45249) (9294.87183 5000.00000)
(9294.87183 5015.08337) (9291.10701 5082.95667) (9294.72432 5113.12217) (9287.18190 5128.20554) (9193.06278 5222.32534)
(9140.27149 5262.90170) (9053.54355 5319.46278) (9008.29468 5341.93982) (8906.48473 5379.79502) (8797.13518 5403.46244)
(8721.71946 5403.32081) (8638.76414 5388.23812) (8559.57862 5364.56425) (8480.39310 5330.91686) (8435.14423 5308.15057)
(8348.41629 5248.72070) (8273.14898 5180.84740) (8220.21120 5116.89333) (8216.44038 3276.77251)))
("SF_SOLAR" 0 ((8223.98190 8005.27896) (8220.21210 8016.59118)))
("SF_SOLAR" 0 ((8227.75170 8092.00611) (8235.29412 8092.00611)))
("SF_ARCHITECTURE" 0 ((8318.24943 3107.08925) (8269.23699 3152.33812) (8242.98360 3182.50351) (8227.75170 3220.21143)))
("SF_ARCHITECTURE" 0 ((9272.24830 3216.44016) (9249.62387 3223.98190) (9219.45701 3223.98190) (8242.83654 3223.97568)
(8227.75170 3220.21143)))
("SF_SOLAR" 0 ((8239.06391 8125.94276) (8235.29412 8118.40113)))
("SF_ARCHITECTURE" 0 ((8235.29412 2055.05305) (8246.60633 2043.74084)))
("SF_ARCHITECTURE" 0 ((8254.14876 2066.36527) (8239.21923 2061.54457) (8235.29412 2055.05305)))
("SF_SOLAR" 0 ((8239.06391 8174.96222) (8239.06391 8197.58665)))
("SF_SOLAR" 0 ((8239.06391 7982.65452) (8246.60633 7960.03020)))
("SF_SOLAR" 0 ((8239.06391 7926.09355) (8239.06391 7937.40577)))
("SF_SOLAR" 0 ((8246.60633 8163.65000) (8250.37613 8144.79638)))
("SF_SOLAR" 0 ((8246.60633 8163.65000) (8273.00057 8167.26618) (8283.11561 8159.87274) (8404.98360 7949.92229)
(8612.36708 7948.71799)))
("SF_SOLAR" 0 ((8250.37613 8035.44502) (8246.60633 8046.75724)))
("SF_ARCHITECTURE" 0 ((8265.46097 2055.05305) (8261.53507 2048.56075) (8246.60633 2043.74084)))
("SF_SOLAR" 0 ((8295.62500 8069.38167) (8283.25781 8099.54751) (8250.37613 8144.79638)))
("SF_ARCHITECTURE" 0 ((8254.14876 2066.36527) (8265.46097 2055.05305)))
("SF_ARCHITECTURE" 0 ((8254.14876 2066.36527) (8265.46097 2076.47330) (8276.77319 2077.67749)))
("SF_SOLAR" 0 ((8261.68835 8005.27896) (8257.91855 8016.59118)))
("SF_SOLAR" 0 ((8261.68835 8069.38167) (8261.68835 8084.46448)))
("SF_SOLAR" 0 ((8261.68835 7926.09355) (8261.68835 7937.40577)))
("SF_ARCHITECTURE" 0 ((8284.31278 2066.36527) (8276.76561 2056.25713) (8265.46097 2055.05305)))
("SF_ARCHITECTURE" 0 ((8284.31278 2066.36527) (8276.77319 2077.67749)))
("SF_ARCHITECTURE" 0 ((8299.39762 2088.98971) (8284.32036 2087.78552) (8276.77319 2077.67749)))
("SF_SOLAR" 0 ((8280.54299 8125.94276) (8288.08541 8129.71335)))
("SF_SOLAR" 0 ((8280.54299 7982.65452) (8284.31278 7960.03020)))
("SF_SOLAR" 0 ((8284.31278 8035.44502) (8284.31278 8046.75724)))
("SF_ARCHITECTURE" 0 ((8284.31278 2066.36527) (8299.39005 2069.24095) (8306.93722 2077.67749)))
("SF_SOLAR" 0 ((8291.85520 8163.65000) (8510.55713 8163.65000)))
("SF_ARCHITECTURE" 0 ((8299.39762 2088.98971) (8306.93722 2077.67749)))
("SF_ARCHITECTURE" 0 ((8322.02206 2100.30192) (8306.94480 2097.42624) (8299.39762 2088.98971)))
("SF_SOLAR" 0 ((8303.16742 8141.02557) (8397.43495 8144.64174) (8408.59389 8137.24830) (8420.05939 8114.63054)))
("SF_SOLAR" 0 ((8306.93722 8182.50385) (8306.93722 8174.96222)))
("SF_SOLAR" 0 ((8306.93722 8069.38167) (8314.47964 8076.92308) (8314.47964 8084.46448)))
("SF_SOLAR" 0 ((8306.93722 8012.82059) (8306.93722 8005.27896)))
("SF_SOLAR" 0 ((8306.93722 7960.03020) (8306.93722 7982.65452)))
("SF_SOLAR" 0 ((8306.93722 7941.17647) (8306.93722 7933.63495)))
("SF_ARCHITECTURE" 0 ((8325.79186 5071.64446) (8306.93722 5086.72658)))
("SF_ARCHITECTURE" 0 ((8329.56165 2088.98971) (8322.01448 2078.88156) (8306.93722 2077.67749)))
("SF_SOLAR" 0 ((8329.56165 8024.13281) (8318.24943 8031.67421)))
("SF_ARCHITECTURE" 0 ((8318.24943 3276.77251) (8352.18699 3276.77251)))
("SF_ARCHITECTURE" 0 ((8325.79186 4355.20362) (8325.79186 3947.96380) (8325.79186 3929.11052) (8325.79186 3714.17839)
(8318.25633 3695.32387) (8318.24943 3276.77251)))
("SF_ARCHITECTURE" 0 ((9181.75057 3110.85973) (9180.54570 3080.70045) (9166.66572 3073.15950) (8827.29921 3073.15882)
(8804.67477 3076.92308) (8416.28959 3076.91686) (8401.20758 3073.30034) (8333.33428 3073.30724) (8319.45430 3084.46482)
(8318.24943 3107.08925)))
("SF_ARCHITECTURE" 0 ((9181.75057 3110.85973) (9147.81391 3110.85973) (8623.67930 3110.85973) (8601.05486 3110.85973)
(8559.57862 3110.85973) (8371.04072 3110.85973) (8318.24943 3107.08925)))
("SF_ARCHITECTURE" 0 ((8491.70532 1542.23133) (8475.57172 1515.83710) (8436.19299 1466.81844) (8411.46267 1425.33937)
(8383.40238 1391.40271) (8318.24943 1289.59276)))
("SF_ARCHITECTURE" 0 ((8322.02206 2100.30192) (8329.56165 2088.98971)))
("SF_ARCHITECTURE" 0 ((8322.02206 2100.30192) (8325.94649 2106.79344) (8355.95871 2121.86991) (8374.81052 2122.92636)))
("SF_SOLAR" 0 ((8329.56165 7978.88394) (8325.79186 7963.80090)))
("SF_ARCHITECTURE" 0 ((8325.79186 4355.20362) (8325.79186 4385.36912) (8325.79186 4438.16029) (8325.79186 4460.78473)
(8325.79186 4573.90690) (8325.79186 4592.76018) (8325.79186 4709.65351) (8325.79186 4732.27794) (8325.79186
5071.64446)))
("SF_ARCHITECTURE" 0 ((8325.79186 5071.64446) (8340.87387 5076.61256) (8374.81052 5105.42613) (8386.12274 5109.35102)))
("SF_ARCHITECTURE" 0 ((8325.79186 4355.20362) (8412.51980 4355.20984) (8435.14423 4358.97477) (8480.39310 4355.20984)
(8533.18156 4358.67828) (8548.26640 4355.20984) (8627.45192 4355.20984) (8661.38857 4358.97477) (8714.17704 4355.20362)
(8736.80147 4358.96787) (8880.09050 4358.97477) (8902.71493 4355.20984) (9177.97794 4355.20362)))
("SF_SOLAR" 0 ((8329.56165 8133.48416) (8337.10407 8125.94276)))
("SF_SOLAR" 0 ((8544.49378 8099.54751) (8521.86934 8103.31176) (8431.37161 8103.31176) (8412.51980 8099.70204)
(8401.20758 8103.17025) (8329.56165 8103.31833)))
("SF_SOLAR" 0 ((8329.56165 8024.13281) (8337.10407 8001.50837)))
("SF_SOLAR" 0 ((8329.56165 8024.13281) (8337.10407 8031.67421) (8337.10407 8039.21561) (8337.10407 8046.75724)))
("SF_ARCHITECTURE" 0 ((8386.12274 2111.61414) (8382.19830 2105.12183) (8348.41629 2090.04604) (8329.56165 2088.98971)))
("SF_SOLAR" 0 ((8352.18609 8133.48416) (8344.64649 8114.63054)))
("SF_SOLAR" 0 ((8348.41629 7986.42534) (8363.49830 7960.03020)))
("SF_SOLAR" 0 ((8367.27093 7993.96674) (8355.96357 7992.76912) (8348.41629 7986.42534)))
("SF_SOLAR" 0 ((8559.57862 8065.61086) (8548.26640 8061.84661) (8352.18609 8058.06946)))
("SF_ARCHITECTURE" 0 ((8352.18699 4325.03812) (8352.18699 4309.95475) (8352.18699 3996.98382) (8352.18699 3974.35939)
(8352.18699 3450.22624) (8352.18699 3431.37229) (8352.18699 3420.06007) (8352.18699 3367.27025) (8352.18699 3348.41629)
(8352.18699 3276.77251)))
("SF_ARCHITECTURE" 0 ((9170.43835 3284.31346) (9147.81391 3273.00814) (8359.72851 3273.00747) (8352.18699 3276.77251)))
("SF_ARCHITECTURE" 0 ((8446.45645 791.85520) (8355.95871 791.85520)))
("SF_SOLAR" 0 ((8371.04072 8069.38167) (8371.04072 8080.69389)))
("SF_SOLAR" 0 ((8559.57862 8024.13281) (8540.72398 8027.89683) (8371.04072 8027.90339)))
("SF_SOLAR" 0 ((8374.81052 7929.86425) (8374.81052 7941.17647)))
("SF_ARCHITECTURE" 0 ((8386.12274 2111.61414) (8374.81052 2122.92636)))
("SF_ARCHITECTURE" 0 ((8408.74717 2138.00905) (8386.12274 2133.18213) (8374.81052 2122.92636)))
("SF_ARCHITECTURE" 0 ((8431.37161 1568.62839) (8421.11652 1557.31618) (8374.81052 1478.13066)))
("SF_SOLAR" 0 ((8378.58314 8118.40113) (8378.58314 8133.48416)))
("SF_ARCHITECTURE" 0 ((8386.12274 5109.35102) (8393.66516 5098.03880)))
("SF_ARCHITECTURE" 0 ((8404.97738 5120.66324) (8390.04864 5115.84287) (8386.12274 5109.35102)))
("SF_ARCHITECTURE" 0 ((8386.12274 5086.72658) (8393.66516 5098.03880)))
("SF_ARCHITECTURE" 0 ((8386.12274 2111.61414) (8401.20758 2112.67048) (8412.51980 2122.92636)))
("SF_SOLAR" 0 ((8389.89536 8035.44502) (8389.89536 8042.98643)))
("SF_SOLAR" 0 ((8491.70532 7997.73756) (8465.30826 7994.11482) (8438.91403 8001.36029) (8420.05939 8001.50181)
(8389.89536 7993.96674)))
("SF_ARCHITECTURE" 0 ((8408.74717 5116.89333) (8404.82274 5105.58733) (8393.66516 5098.03880)))
("SF_SOLAR" 0 ((8397.43495 8084.46448) (8397.43495 8069.38167)))
("SF_SOLAR" 0 ((8401.20758 8016.59118) (8408.74717 8009.04977)))
("SF_ARCHITECTURE" 0 ((8404.97738 5049.02002) (8401.20758 5052.78993) (8401.20758 5064.10215)))
("SF_ARCHITECTURE" 0 ((8401.20758 5064.10215) (8382.35294 5063.94819) (8374.81052 5060.17726) (8363.49921 5045.24887)
(8363.49921 4996.22885) (8363.49921 4509.80351) (8363.49921 4490.95023) (8363.49921 4411.76471) (8371.04072 4398.03450)
(8393.65826 4401.65011) (8401.20758 4407.99355)))
("SF_ARCHITECTURE" 0 ((8401.20758 5064.10215) (8405.13201 5070.59400) (8416.28959 5075.41437)))
("SF_ARCHITECTURE" 0 ((8401.20758 4407.99355) (8668.92817 4407.98733) (8691.55260 4404.37149) (8714.02998 4409.19830)
(8721.57104 4423.07692) (8725.49016 5199.84253) (8714.17217 5207.23609) (8672.70079 5202.57014) (8536.95419
5154.59989)))
("SF_ARCHITECTURE" 0 ((8404.97738 5049.02002) (8394.71459 5033.93665) (8389.90023 5015.08337) (8393.66516 4984.91663)
(8393.66516 4498.49129) (8393.66516 4483.40916) (8389.90023 4434.38914) (8401.20758 4407.99355)))
("SF_SOLAR" 0 ((8423.83201 7975.11312) (8404.97738 7967.57172)))
("SF_ARCHITECTURE" 0 ((8408.74717 5116.89333) (8404.97738 5116.89333) (8404.97738 5120.66324)))
("SF_ARCHITECTURE" 0 ((8404.97738 5120.66324) (8412.51980 5124.43439)))
("SF_ARCHITECTURE" 0 ((8404.97738 5049.02002) (8423.83201 5067.87330)))
("SF_ARCHITECTURE" 0 ((8408.74717 5116.89333) (8412.51980 5124.43439)))
("SF_ARCHITECTURE" 0 ((8450.22624 4264.70588) (8442.68473 4279.78880) (8431.37161 4276.01810) (8420.05939 4274.81391)
(8408.74717 4264.70588)))
("SF_ARCHITECTURE" 0 ((8412.51980 2122.92636) (8408.74717 2126.69683) (8408.74717 2138.00905)))
("SF_ARCHITECTURE" 0 ((8446.45645 2145.55079) (8420.05939 2145.39615) (8408.74717 2138.00905)))
("SF_ARCHITECTURE" 0 ((8408.74808 3386.12342) (8408.74808 3397.43563) (8423.83201 3408.74785)))
("SF_ARCHITECTURE" 0 ((8408.74808 3355.95803) (8408.74808 3363.49898)))
("SF_ARCHITECTURE" 0 ((8408.74808 3333.33360) (8408.74808 3323.22545) (8446.45645 3322.02138)))
("SF_SOLAR" 0 ((8420.05939 7922.32274) (8412.51980 7937.40577)))
("SF_ARCHITECTURE" 0 ((9177.97794 4355.20362) (9181.74367 4366.51584) (9181.75543 4543.74016) (9185.51414 4562.59468)
(9184.31550 5071.64446) (9095.02262 5146.00215) (9008.29468 5198.79921) (8910.25735 5236.50679) (8872.54808 5244.94977)
(8804.67477 5252.49152) (8717.94966 5252.49152) (8680.24038 5248.72070) (8627.45192 5236.50679) (8552.03620 5210.11176)
(8514.32975 5191.25792) (8412.51980 5124.43439)))
("SF_ARCHITECTURE" 0 ((8412.51980 4230.76923) (8412.51980 4242.08145)))
("SF_ARCHITECTURE" 0 ((8412.51980 2122.92636) (8431.37161 2123.97579) (8450.22624 2134.23857)))
("SF_SOLAR" 0 ((8442.68382 8141.02557) (8416.28959 8141.02557)))
("SF_SOLAR" 0 ((8423.83201 7975.11312) (8416.28959 7990.19615)))
("SF_ARCHITECTURE" 0 ((8416.28959 5075.41437) (8423.83201 5067.87330)))
("SF_ARCHITECTURE" 0 ((8438.91403 5084.84163) (8427.60181 5085.51934) (8416.28959 5075.41437)))
("SF_SOLAR" 0 ((8420.05939 8069.38167) (8420.05939 8084.46448)))
("SF_SOLAR" 0 ((8420.05939 8039.21561) (8420.05939 8046.75724)))
("SF_ARCHITECTURE" 0 ((8427.60181 4166.66708) (8416.44423 4177.97930) (8420.05939 4204.37364)))
("SF_SOLAR" 0 ((8423.83201 7975.11312) (8431.37919 7971.49038) (8487.93269 7971.34231)))
("SF_ARCHITECTURE" 0 ((8438.91403 5084.84163) (8434.98891 5071.80192) (8423.83201 5067.87330)))
("SF_ARCHITECTURE" 0 ((9057.31618 4264.70588) (9064.85667 4242.08145) (9064.85667 3401.20690) (9064.85667 3386.12342)
(9064.85667 3367.27025) (9059.88801 3348.57093) (9049.77376 3344.65271) (8446.45645 3344.80045) (8436.34762 3352.19367)
(8434.98891 3397.43563) (8423.83201 3408.74785)))
("SF_ARCHITECTURE" 0 ((8427.60181 4166.66708) (8423.83688 4144.04265) (8423.83201 3408.74785)))
("SF_ARCHITECTURE" 0 ((8450.22624 4264.70588) (8442.68473 4242.08145) (8442.68473 4215.68586) (8442.68473 4181.74921)
(8427.60181 4166.66708)))
("SF_ARCHITECTURE" 0 ((8431.37161 1568.62839) (8442.68382 1561.08597)))
("SF_ARCHITECTURE" 0 ((8431.37161 1568.62839) (8436.19299 1579.78529) (8442.68382 1583.71041)))
("SF_ARCHITECTURE" 0 ((8431.37161 1530.91912) (8441.62817 1549.77376) (8442.68382 1561.08597)))
("SF_SOLAR" 0 ((8438.91403 8039.21561) (8438.91403 8046.75724)))
("SF_ARCHITECTURE" 0 ((8438.91403 5084.84163) (8442.68382 5082.95667) (8448.33993 5092.38269)))
("SF_ARCHITECTURE" 0 ((8438.91403 5084.84163) (8448.33993 5092.38269)))
("SF_SOLAR" 0 ((8442.68382 8182.50385) (8442.68382 8174.96222)))
("SF_SOLAR" 0 ((8518.09955 8141.02557) (8442.68382 8141.02557)))
("SF_SOLAR" 0 ((8442.68382 8141.02557) (8442.68382 8114.63054)))
("SF_SOLAR" 0 ((8442.68382 8084.46448) (8442.68382 8069.38167)))
("SF_ARCHITECTURE" 0 ((8453.99604 1579.94061) (8442.68382 1583.71041)))
("SF_ARCHITECTURE" 0 ((8453.99604 1606.33484) (8443.88869 1598.78756) (8442.68382 1583.71041)))
("SF_ARCHITECTURE" 0 ((8453.99604 1579.94061) (8449.17681 1565.01109) (8442.68382 1561.08597)))
("SF_SOLAR" 0 ((8446.45645 8016.59118) (8450.22624 8009.04977)))
("SF_ARCHITECTURE" 0 ((8446.45645 2145.55079) (8450.22624 2134.23857)))
("SF_ARCHITECTURE" 0 ((8446.45645 2145.55079) (8454.00362 2155.65882) (8484.16290 2156.86301)))
("SF_ARCHITECTURE" 0 ((8476.62048 814.47964) (8446.45645 814.47964)))
("SF_ARCHITECTURE" 0 ((8446.45645 814.47964) (8446.45645 791.85520)))
("SF_ARCHITECTURE" 0 ((8533.18156 463.80090) (8536.79887 441.17647) (8529.40486 431.06912) (8480.39310 426.24152)
(8295.62500 426.24152) (8246.61256 430.01889) (8236.35045 441.17647) (8240.26878 806.93235) (8246.61324 813.27477)
(8269.23077 818.24457) (8295.62500 814.48586) (8446.45645 814.47964)))
("SF_ARCHITECTURE" 0 ((8476.62048 795.62500) (8446.45645 791.85520)))
("SF_ARCHITECTURE" 0 ((8448.33993 5092.38269) (8453.99604 5101.80995) (8457.76867 5101.80995)))
("SF_ARCHITECTURE" 0 ((8448.33993 5092.38269) (8457.76867 5098.03880) (8457.76867 5101.80995)))
("SF_ARCHITECTURE" 0 ((8450.22624 4264.70588) (8514.32975 4268.47704) (8548.26640 4264.71210) (8989.44287 4268.47704)
(9057.31618 4264.70588)))
("SF_ARCHITECTURE" 0 ((8484.16290 2156.86301) (8472.84446 2139.21324) (8450.22624 2134.23857)))
("SF_ARCHITECTURE" 0 ((8453.99604 1606.33484) (8461.53846 1602.56505)))
("SF_ARCHITECTURE" 0 ((8457.76867 1621.41686) (8453.99604 1606.33484)))
("SF_ARCHITECTURE" 0 ((8453.99604 1579.94061) (8460.34050 1587.48778) (8461.53846 1602.56505)))
("SF_SOLAR" 0 ((8461.53846 7978.88394) (8457.76867 7986.42534)))
("SF_ARCHITECTURE" 0 ((8465.30826 5105.58111) (8457.76867 5101.80995)))
("SF_ARCHITECTURE" 0 ((8472.85068 1621.41686) (8471.64581 1610.11222) (8461.53846 1602.56505)))
("SF_SOLAR" 0 ((8465.30826 8133.48416) (8465.30826 8118.40113)))
("SF_SOLAR" 0 ((8465.30826 8069.38167) (8465.30826 8084.46448)))
("SF_SOLAR" 0 ((8465.30826 8035.44502) (8465.30826 8050.52783)))
("SF_SOLAR" 0 ((8465.30826 7941.17647) (8465.30826 7933.63495)))
("SF_ARCHITECTURE" 0 ((8472.85068 5113.12217) (8469.08088 5105.58111) (8465.30826 5105.58111)))
("SF_ARCHITECTURE" 0 ((8472.85068 5113.12217) (8465.30826 5109.35102) (8465.30826 5105.58111)))
("SF_ARCHITECTURE" 0 ((8472.85068 1621.41686) (8465.30826 1636.50170)))
("SF_ARCHITECTURE" 0 ((8484.16290 2205.88235) (8476.62048 2207.08654) (8469.08088 2217.19457)))
("SF_ARCHITECTURE" 0 ((8721.71946 2258.67296) (8665.15837 2258.52523) (8529.41176 2239.67127) (8480.39310 2227.45045)
(8469.08088 2217.19457)))
("SF_ARCHITECTURE" 0 ((8484.16290 5116.89333) (8472.85068 5113.12217)))
("SF_ARCHITECTURE" 0 ((8472.85068 1621.41686) (8482.95803 1628.96550) (8484.16290 1640.27149)))
("SF_ARCHITECTURE" 0 ((8476.62048 4573.90690) (8538.00294 4671.94570) (8601.05486 4754.90238)))
("SF_ARCHITECTURE" 0 ((8503.01753 814.47964) (8476.62048 814.47964)))
("SF_ARCHITECTURE" 0 ((8476.62048 814.47964) (8476.62048 795.62500)))
("SF_ARCHITECTURE" 0 ((8487.93269 791.85520) (8476.62048 795.62500)))
("SF_ARCHITECTURE" 0 ((8484.16290 1640.27149) (8480.39310 1647.81391)))
("SF_ARCHITECTURE" 0 ((8491.70532 5124.43439) (8487.93269 5124.43439) (8484.16290 5116.89333)))
("SF_ARCHITECTURE" 0 ((8491.70532 5124.43439) (8491.70532 5120.66324) (8484.16290 5116.89333)))
("SF_ARCHITECTURE" 0 ((8665.15837 3322.02138) (8484.16290 3322.02138)))
("SF_ARCHITECTURE" 0 ((8484.16290 2156.86301) (8506.78733 2157.01075) (8597.28507 2179.33971) (8631.22172 2179.48744)))
("SF_ARCHITECTURE" 0 ((8484.16290 1640.27149) (8494.41878 1647.81878) (8544.49378 1730.76923)))
("SF_SOLAR" 0 ((8487.93269 8114.63054) (8487.93269 8133.48416)))
("SF_SOLAR" 0 ((8487.93269 8084.46448) (8487.93269 8069.38167)))
("SF_SOLAR" 0 ((8487.93269 8050.52783) (8487.93269 8039.21561)))
("SF_SOLAR" 0 ((8491.70532 7997.73756) (8487.93269 8020.36199)))
("SF_SOLAR" 0 ((8487.93269 7971.34231) (8487.93269 7986.42534)))
("SF_SOLAR" 0 ((8529.41176 7971.34231) (8487.93269 7971.34231)))
("SF_SOLAR" 0 ((8487.93269 7877.07387) (8533.18156 7877.07387)))
("SF_SOLAR" 0 ((8491.70532 7997.73756) (8518.09955 7993.96674) (8574.66063 7994.11482) (8585.97285 7997.73756)))
("SF_ARCHITECTURE" 0 ((8491.70532 5124.43439) (8499.24491 5128.20554)))
("SF_ARCHITECTURE" 0 ((8506.78733 5133.86165) (8503.01753 5135.74661) (8499.24491 5128.20554)))
("SF_ARCHITECTURE" 0 ((8506.78733 5133.86165) (8499.24491 5128.20554)))
("SF_ARCHITECTURE" 0 ((8503.01753 814.47964) (8511.61425 788.08541) (8529.41176 773.00057)))
("SF_ARCHITECTURE" 0 ((8503.01753 814.47964) (8525.64197 818.09615) (8535.89706 810.70226) (8540.56934 788.08541)
(8529.41176 773.00057)))
("SF_ARCHITECTURE" 0 ((8506.78733 5133.86165) (8521.86934 5153.39604) (8536.95419 5154.59989)))
("SF_ARCHITECTURE" 0 ((8506.78733 5133.86165) (8529.26335 5136.95079) (8536.95419 5154.59989)))
("SF_SOLAR" 0 ((8510.55713 8197.58665) (8511.61425 8178.73303) (8543.30351 8122.17195) (8635.35475 7921.48710)
(8657.61595 7904.52534) (8676.47059 7903.31448) (8691.55260 7895.92760)))
("SF_SOLAR" 0 ((8510.55713 8129.71335) (8510.55713 8114.63054)))
("SF_SOLAR" 0 ((8510.55713 8005.27896) (8510.55713 8016.59118)))
("SF_SOLAR" 0 ((8510.55713 7986.42534) (8510.55713 7978.88394)))
("SF_ARCHITECTURE" 0 ((8521.86934 4713.42342) (8556.86312 4769.83665) (8567.11821 4777.52681)))
("SF_ARCHITECTURE" 0 ((8533.18156 463.80090) (8536.79887 501.50735) (8525.64197 512.81957)))
("SF_ARCHITECTURE" 0 ((8533.18156 463.80090) (8517.80339 463.50475) (8514.03281 467.27523) (8511.61425 497.73756)
(8518.24038 508.89514) (8525.64197 512.81957)))
("SF_ARCHITECTURE" 0 ((8525.64197 512.81957) (8525.64683 742.83654) (8529.41176 773.00057)))
("SF_SOLAR" 0 ((8529.41176 8073.15226) (8529.41176 8080.69389)))
("SF_SOLAR" 0 ((8529.41176 7971.34231) (8548.26640 7967.72636) (8563.34842 7978.88394)))
("SF_SOLAR" 0 ((8529.41176 7971.34231) (8533.18156 7975.11312) (8533.18156 7986.42534)))
("SF_SOLAR" 0 ((8533.18156 8001.50837) (8533.18156 8016.59118)))
("SF_SOLAR" 0 ((8536.95419 8042.98643) (8544.49378 8046.75724)))
("SF_ARCHITECTURE" 0 ((8540.72398 6444.19299) (8544.64910 6346.15385) (8552.04310 6336.04615) (8563.34842 6334.84163)
(8823.37477 6336.04615) (8827.14593 6342.38959) (8829.87319 6391.40271) (8827.44762 6429.11018) (8834.84163
6444.19299)))
("SF_SOLAR" 0 ((8544.49378 8201.35747) (8565.92104 8163.65000) (8568.17534 8152.33778) (8611.17681 8069.38167)
(8671.80452 7937.40577) (8691.55260 7915.97907) (8710.40724 7911.01708) (9328.80939 7911.00396) (9377.82805
7907.23982)))
("SF_SOLAR" 0 ((8559.57862 8024.13281) (8563.34842 8005.27896)))
("SF_SOLAR" 0 ((8559.57862 8024.13281) (8563.34842 8027.90339) (8574.66063 8027.90339)))
("SF_SOLAR" 0 ((8567.11821 7877.07387) (8616.13971 7877.07387)))
("SF_ARCHITECTURE" 0 ((8567.11821 4777.52681) (8574.66753 4774.05837) (8582.19548 4777.68077) (8588.39084 4788.68405)
(8582.20305 4792.60894)))
("SF_ARCHITECTURE" 0 ((8567.11821 4777.52681) (8571.04412 4788.68405) (8582.20305 4792.60894)))
("SF_SOLAR" 0 ((8570.89084 7982.65452) (8582.20305 7963.80090)))
("SF_SOLAR" 0 ((8778.28054 8144.79638) (8777.08609 8152.34762) (8767.27138 8163.94615) (8574.66063 8163.65000)))
("SF_ARCHITECTURE" 0 ((8585.97285 4800.15124) (8582.20305 4800.15124) (8582.20305 4792.60894)))
("SF_ARCHITECTURE" 0 ((8582.20305 4792.60894) (8585.97285 4800.15124)))
("SF_SOLAR" 0 ((8778.28054 8144.79638) (8755.65611 8141.03213) (8585.97285 8141.02557)))
("SF_ARCHITECTURE" 0 ((8593.51527 4807.69231) (8589.74265 4807.69231) (8585.97285 4800.15124)))
("SF_ARCHITECTURE" 0 ((8593.51527 4807.69231) (8593.51527 4803.92115) (8585.97285 4800.15124)))
("SF_ARCHITECTURE" 0 ((8593.51527 4807.69231) (8605.88314 4834.08790) (8633.94276 4868.02455) (8656.41256 4901.95430)
(8657.61595 4909.50226)))
("SF_SOLAR" 0 ((8793.36256 8099.54751) (8631.22172 8099.69548) (8604.82749 8107.08891)))
("SF_SOLAR" 0 ((8623.67930 8118.40113) (8616.13971 8133.48416)))
("SF_SOLAR" 0 ((8616.13971 8020.36199) (8616.13971 8027.90351)))
("SF_SOLAR" 0 ((8823.52941 8058.06946) (8808.44740 8061.83348) (8710.40724 8061.83348) (8691.55260 8058.22398)
(8680.24038 8061.69208) (8650.07636 8058.36550) (8627.45192 8061.84005)))
("SF_ARCHITECTURE" 0 ((8627.45192 5286.57658) (8653.84615 5293.96957) (8714.17704 5301.51086) (8842.38405 5297.88880)))
("SF_ARCHITECTURE" 0 ((8631.22172 2179.48744) (8661.38857 2149.32127)))
("SF_ARCHITECTURE" 0 ((8665.15837 2194.57014) (8646.30373 2193.51380) (8635.14683 2186.88688) (8631.22172 2179.48744)))
("SF_SOLAR" 0 ((8638.76414 7975.11312) (8638.76414 7982.65452)))
("SF_SOLAR" 0 ((8642.53394 8027.90351) (8819.75962 8027.90351) (8831.07183 8027.90351)))
("SF_SOLAR" 0 ((8646.30373 8133.48416) (8646.30373 8118.40113)))
("SF_SOLAR" 0 ((8646.30373 8069.38167) (8646.30373 8084.46448)))
("SF_ARCHITECTURE" 0 ((8646.30464 358.22115) (8646.30373 350.67873)))
("SF_ARCHITECTURE" 0 ((8646.30464 886.12274) (8668.92817 886.12274)))
("SF_ARCHITECTURE" 0 ((8646.30464 886.12274) (8646.30464 878.57557) (8646.30464 867.27093)))
("SF_ARCHITECTURE" 0 ((8646.30464 867.27093) (8668.92817 867.27093)))
("SF_ARCHITECTURE" 0 ((8646.30464 844.64649) (8646.30464 852.19367) (8646.30464 867.27093)))
("SF_ARCHITECTURE" 0 ((8646.30464 844.64649) (8668.92817 844.64649)))
("SF_ARCHITECTURE" 0 ((8646.30464 844.64649) (8646.30464 833.33428) (8646.30464 799.39762) (8661.38857 788.08541)))
("SF_ARCHITECTURE" 0 ((8646.30464 358.22115) (8668.92817 358.22115)))
("SF_ARCHITECTURE" 0 ((8646.30464 358.22115) (8646.30464 369.53337) (8646.30464 377.07296) (8646.30464 422.32183)
(8646.30464 429.85735) (8661.38857 437.40667)))
("SF_ARCHITECTURE" 0 ((8650.07636 2413.27274) (8657.46821 2398.19005) (8657.61595 2364.25339)))
("SF_ARCHITECTURE" 0 ((8650.07636 2413.27274) (8646.15667 2484.91731) (8635.29536 2549.01934) (8642.54084 2560.17692)
(8653.84615 2564.09593) (8815.83371 2562.89864) (8819.60430 2556.55419) (8819.61120 2518.85396) (8804.67477
2417.04400)))
("SF_ARCHITECTURE" 0 ((8748.11369 3597.28507) (8737.85860 3589.73710) (8686.73337 3506.78733) (8653.84615 3461.53846)))
("SF_SOLAR" 0 ((8657.61595 7993.96674) (8846.15385 7993.81210) (8856.40973 7986.41867) (8868.77828 7963.80090)))
("SF_ARCHITECTURE" 0 ((8657.61595 2364.25339) (8668.93575 2345.55407) (8684.01301 2341.62896) (8782.05034 2341.78360)
(8789.43812 2345.55407) (8800.90498 2364.25339)))
("SF_ARCHITECTURE" 0 ((8665.15837 2194.57014) (8671.64367 2183.25792) (8672.54548 2164.40396) (8661.38857 2149.32127)))
("SF_ARCHITECTURE" 0 ((8661.38857 788.08541) (8661.38857 437.40667)))
("SF_ARCHITECTURE" 0 ((8668.92817 844.64649) (8668.77489 799.39762) (8661.38857 788.08541)))
("SF_ARCHITECTURE" 0 ((8668.92817 358.22115) (8668.78111 392.15781) (8661.38857 437.40667)))
("SF_ARCHITECTURE" 0 ((8665.15837 2194.57014) (8668.92817 2202.11188)))
("SF_SOLAR" 0 ((8668.92817 8118.40113) (8668.92817 8133.48416)))
("SF_SOLAR" 0 ((8668.92817 8088.23529) (8668.92817 8069.38167)))
("SF_ARCHITECTURE" 0 ((8668.92817 935.14333) (8672.70079 920.05939) (8668.92817 886.12274)))
("SF_ARCHITECTURE" 0 ((8668.92817 886.12274) (8668.92817 867.27093)))
("SF_ARCHITECTURE" 0 ((8668.92817 844.64649) (8668.92817 867.27093)))
("SF_ARCHITECTURE" 0 ((8668.92817 358.22115) (8672.55238 339.36652) (8672.70079 271.49321)))
("SF_SOLAR" 0 ((8676.47059 8016.59118) (8672.70079 8005.27896)))
("SF_SOLAR" 0 ((8883.86029 7948.71799) (8770.73812 7948.72455) (8748.11369 7952.48869) (8687.78281 7952.34061)
(8676.47059 7948.71799)))
("SF_SOLAR" 0 ((8687.78281 8046.75724) (8680.24038 8039.21561)))
("SF_SOLAR" 0 ((8691.55260 7967.57172) (8691.55260 7978.88394) (8687.78281 7982.65452)))
("SF_SOLAR" 0 ((8691.55260 8133.48416) (8691.55260 8118.40113)))
("SF_SOLAR" 0 ((8706.63744 7846.90803) (8691.55260 7895.92760)))
("SF_SOLAR" 0 ((8699.09502 7903.46912) (8691.55260 7895.92760)))
("SF_SOLAR" 0 ((8699.09502 8088.23529) (8702.86482 8073.15226)))
("SF_SOLAR" 0 ((8706.63744 7846.90803) (9762.89434 7846.90803) (9788.83767 7869.37783) (9966.06335 7869.53903)
(10003.76980 7873.30317)))
("SF_SOLAR" 0 ((8714.17704 8001.50837) (8714.17704 8012.82059) (8710.40724 8016.59118)))
("SF_SOLAR" 0 ((8714.17704 8118.40113) (8714.17704 8133.48416)))
("SF_SOLAR" 0 ((8714.17704 8035.44502) (8714.17704 8050.52783)))
("SF_SOLAR" 0 ((8714.17704 7982.65452) (8714.17704 7967.57172)))
("SF_ARCHITECTURE" 0 ((9392.91097 237.55656) (9391.70667 2017.34514) (9381.59785 2027.60792) (9272.24830 2099.25238)
(9159.12613 2159.72557) (9079.94061 2193.52070) (8974.35803 2227.45735) (8887.63292 2247.21301) (8789.59276 2258.52523)
(8721.71946 2258.67296)))
("SF_ARCHITECTURE" 0 ((8721.71946 241.32636) (8725.49016 354.44853) (8725.49016 377.07296) (8725.49016 478.88292)
(8725.49016 501.50735) (8725.49016 531.67421) (8725.49016 859.72851) (8725.49016 882.35294) (8725.49016 957.76867)
(8725.49016 976.62048) (8725.49016 1210.40724) (8725.49016 1233.03167) (8721.72568 1836.34966) (8725.48925 1858.97410)
(8721.72636 1915.53518) (8725.48439 1934.38914) (8725.48439 2100.30192) (8721.72568 2119.15509) (8721.72568 2205.88235)
(8725.48439 2239.81900) (8721.71946 2258.67296)))
("SF_ARCHITECTURE" 0 ((8721.71946 241.32636) (8740.57410 237.55656) (9309.95475 237.56278) (9321.26697 241.32636)))
("SF_ARCHITECTURE" 0 ((8793.36256 3759.42726) (8725.48925 3668.92952)))
("SF_SOLAR" 0 ((8729.26188 8088.23529) (8729.26188 8069.38167)))
("SF_SOLAR" 0 ((8736.80147 8133.48416) (8736.80147 8118.40113)))
("SF_SOLAR" 0 ((8736.80147 8050.52783) (8736.80147 8039.21561)))
("SF_SOLAR" 0 ((8736.80147 8016.59118) (8736.80147 8001.50837)))
("SF_SOLAR" 0 ((8736.80147 7982.65452) (8736.80147 7967.57172)))
("SF_SOLAR" 0 ((8812.21719 7877.07387) (8740.57410 7877.07387)))
("SF_ARCHITECTURE" 0 ((8766.96833 3612.36776) (8763.04321 3594.86708) (8748.11369 3597.28507)))
("SF_ARCHITECTURE" 0 ((8748.11369 3597.28507) (8759.42590 3612.36776)))
("SF_SOLAR" 0 ((8759.42590 8118.40113) (8759.42590 8133.48416)))
("SF_SOLAR" 0 ((8759.42590 8088.23529) (8759.42590 8069.38167)))
("SF_SOLAR" 0 ((8759.42590 8039.21561) (8759.42590 8050.52783)))
("SF_SOLAR" 0 ((8759.42590 8001.50837) (8759.42590 8016.59118)))
("SF_SOLAR" 0 ((8759.42590 7986.42534) (8759.42590 7967.57172)))
("SF_ARCHITECTURE" 0 ((8766.96833 3612.36776) (8759.42590 3612.36776)))
("SF_ARCHITECTURE" 0 ((8770.73812 3631.22172) (8764.24729 3627.29661) (8759.42590 3612.36776)))
("SF_ARCHITECTURE" 0 ((8766.96833 4404.22364) (8782.05034 4400.60713) (8793.36256 4407.99355)))
("SF_ARCHITECTURE" 0 ((8766.96833 3612.36776) (8777.07568 3619.91572) (8778.28054 3631.22172)))
("SF_ARCHITECTURE" 0 ((8770.73812 3631.22172) (8778.28054 3631.22172)))
("SF_ARCHITECTURE" 0 ((8770.73812 3631.22172) (8771.94299 3642.52771) (8782.05034 3650.07500)))
("SF_ARCHITECTURE" 0 ((8770.73812 312.97229) (8774.49695 297.88744) (8770.73812 286.57523)))
("SF_ARCHITECTURE" 0 ((8774.51075 935.14423) (8782.05034 935.14423)))
("SF_SOLAR" 0 ((8778.28054 8144.79638) (8785.82296 8141.02557)))
("SF_ARCHITECTURE" 0 ((8789.59276 3646.30509) (8788.38790 3638.76278) (8778.28054 3631.22172)))
("SF_SOLAR" 0 ((8789.59276 8178.73303) (8782.05034 8197.58665)))
("SF_SOLAR" 0 ((8782.05034 8163.65000) (8793.36256 8168.93767) (8808.44740 8163.65000)))
("SF_SOLAR" 0 ((8782.05034 8088.23529) (8782.05034 8069.38167)))
("SF_SOLAR" 0 ((8785.82296 8050.52783) (8782.05034 8039.21561)))
("SF_SOLAR" 0 ((8782.05034 8016.59118) (8782.05034 8005.27896)))
("SF_ARCHITECTURE" 0 ((8782.05034 3650.07500) (8789.59276 3646.30509)))
("SF_ARCHITECTURE" 0 ((8800.90498 3665.15837) (8793.35769 3667.72477) (8785.97624 3664.10170) (8782.05034 3650.07500)))
("SF_ARCHITECTURE" 0 ((8785.82296 889.89536) (8779.62624 897.44253) (8782.05034 935.14423)))
("SF_ARCHITECTURE" 0 ((9283.56052 938.91403) (9268.47568 942.67896) (8838.61143 942.67896) (8782.05034 935.14423)))
("SF_SOLAR" 0 ((8804.67477 8095.77670) (8786.87862 8129.71335) (8785.82296 8141.02557)))
("SF_SOLAR" 0 ((8800.90498 8144.79638) (8785.82296 8141.02557)))
("SF_ARCHITECTURE" 0 ((8785.82296 2145.55079) (8785.82783 1904.22296) (8789.59276 1881.59853) (8789.58654 1798.64253)
(8785.82783 1779.78790) (8789.59276 1353.69627) (8785.82783 1331.07183) (8785.82296 1040.72398)))
("SF_ARCHITECTURE" 0 ((8785.82296 2145.55079) (8774.65848 2164.40396) (8774.65848 2183.25792) (8782.19876 2198.18597)
(8793.36256 2201.95724) (8815.98699 2197.13654) (8827.29921 2183.25792)))
("SF_ARCHITECTURE" 0 ((8785.82296 2145.55079) (8827.29921 2183.25792)))
("SF_ARCHITECTURE" 0 ((8785.82296 1040.72398) (8812.21719 999.24491)))
("SF_ARCHITECTURE" 0 ((8785.82296 1040.72398) (8778.42138 1036.79887) (8770.73903 1025.64197) (8770.73903 1003.01753)
(8785.82296 991.85860) (8804.66991 992.90249) (8812.21719 999.24491)))
("SF_ARCHITECTURE" 0 ((8785.82296 889.89536) (8785.82919 369.53337) (8789.74740 358.22602) (8800.90498 350.67873)))
("SF_ARCHITECTURE" 0 ((8785.82296 889.89536) (8808.44740 897.43009) (9276.01810 901.20000) (9287.17568 897.28167)
(9291.10011 886.12274)))
("SF_ARCHITECTURE" 0 ((8800.90498 3665.15837) (8799.70011 3653.85238) (8789.59276 3646.30509)))
("SF_ARCHITECTURE" 0 ((9113.87726 4407.99355) (8793.36256 4407.99355)))
("SF_ARCHITECTURE" 0 ((9053.54355 5109.35102) (8978.13066 5153.69186) (8902.71493 5187.48111) (8857.46606 5199.70090)
(8800.90498 5203.46527) (8790.79762 5196.07195) (8789.59276 5135.74661) (8789.59276 4449.47251) (8793.36256
4407.99355)))
("SF_ARCHITECTURE" 0 ((8793.36256 3759.42726) (8804.67477 3755.65611)))
("SF_ARCHITECTURE" 0 ((8793.36256 3759.42726) (8798.18394 3770.58450) (8804.67477 3774.50939)))
("SF_ARCHITECTURE" 0 ((8800.90498 3665.15837) (8814.93824 3676.47059) (8865.00848 3755.65611)))
("SF_ARCHITECTURE" 0 ((9340.12161 2168.17523) (9226.99943 2238.76957) (9091.25283 2299.09423) (8947.96380 2345.25170)
(8929.10916 2345.54717) (8827.29921 2364.10566) (8800.90498 2364.25339)))
("SF_ARCHITECTURE" 0 ((8800.90498 2364.25339) (8797.28224 2386.87783) (8804.67477 2417.04400)))
("SF_SOLAR" 0 ((8804.67477 8095.77670) (8812.21719 8073.15226)))
("SF_SOLAR" 0 ((8804.67477 8095.77670) (8823.52941 8103.31833)))
("SF_SOLAR" 0 ((8804.67477 7982.65452) (8800.90498 7975.11312) (8804.67477 7967.57172)))
("SF_ARCHITECTURE" 0 ((8815.98699 3774.50939) (8804.67477 3774.50939)))
("SF_ARCHITECTURE" 0 ((8804.67477 3774.50939) (8805.87964 3782.05792) (8815.98699 3793.36391)))
("SF_ARCHITECTURE" 0 ((8804.67477 3748.11505) (8804.67477 3755.65611)))
("SF_ARCHITECTURE" 0 ((8815.98699 3774.50939) (8811.16776 3759.58122) (8804.67477 3755.65611)))
("SF_ARCHITECTURE" 0 ((9506.03224 2096.53066) (9494.71516 2111.46561) (9392.91007 2193.52070) (9294.87274 2257.48190)
(9200.60238 2306.64287) (9064.85577 2363.19706) (8966.81844 2393.36312) (8891.40271 2409.35452) (8815.98699 2413.42048)
(8804.67477 2417.04400)))
("SF_SOLAR" 0 ((8808.44740 8163.65000) (9023.37952 8163.65000)))
("SF_SOLAR" 0 ((8876.32070 8027.90351) (8866.20566 8039.21572) (8860.03869 8061.84016) (8843.57432 8084.46448)
(8808.44740 8163.65000)))
("SF_SOLAR" 0 ((8808.44740 8005.27896) (8808.44740 8016.59118)))
("SF_ARCHITECTURE" 0 ((9294.87274 999.24491) (8812.21719 999.24491)))
("SF_ARCHITECTURE" 0 ((8823.52941 3789.59276) (8815.98699 3793.36391)))
("SF_ARCHITECTURE" 0 ((8827.29921 3812.21719) (8817.19186 3800.91120) (8815.98699 3793.36391)))
("SF_ARCHITECTURE" 0 ((8815.98699 3774.50939) (8823.52941 3782.05170) (8823.52941 3789.59276)))
("SF_SOLAR" 0 ((8823.52941 8058.06946) (8831.07183 8027.90351)))
("SF_SOLAR" 0 ((8823.52941 8058.06946) (8834.84163 8080.69389)))
("SF_ARCHITECTURE" 0 ((8823.52941 3789.59276) (8833.63676 3797.14072) (8834.84163 3808.44604)))
("SF_SOLAR" 0 ((8827.29921 8141.02568) (8853.69536 8141.02568)))
("SF_SOLAR" 0 ((8827.29921 7967.57172) (8827.29921 7982.65452)))
("SF_ARCHITECTURE" 0 ((8827.29921 3812.21719) (8834.84163 3808.44604)))
("SF_ARCHITECTURE" 0 ((8827.29921 3812.21719) (8828.50407 3823.52319) (8838.61143 3831.07048)))
("SF_ARCHITECTURE" 0 ((8906.48473 2175.71618) (8861.23586 2183.11018) (8827.29921 2183.25792)))
("SF_SOLAR" 0 ((8846.15385 8005.27896) (8831.07183 8027.90351)))
("SF_ARCHITECTURE" 0 ((9430.61934 6489.44186) (8849.92364 6489.28710) (8834.99005 6480.85068) (8828.35633 6470.58824)
(8828.35633 6455.50554) (8834.84163 6444.19299)))
("SF_ARCHITECTURE" 0 ((9479.63801 6451.73462) (9460.78337 6444.19955) (8834.84163 6444.19299)))
("SF_ARCHITECTURE" 0 ((8834.84163 3808.44604) (8845.99921 3812.37183) (8849.92364 3823.52941)))
("SF_SOLAR" 0 ((8838.61143 8061.84005) (8846.15385 8061.84005)))
("SF_ARCHITECTURE" 0 ((8838.61143 3831.07048) (8849.92364 3823.52941)))
("SF_ARCHITECTURE" 0 ((8838.61143 3831.07048) (8839.81629 3842.37647) (8849.92364 3849.92500)))
("SF_ARCHITECTURE" 0 ((9291.10011 361.99095) (9287.17568 350.83337) (9276.01810 346.91516) (8842.38405 346.90894)))
("SF_SOLAR" 0 ((8844.26844 8027.90351) (8846.15385 8027.90351) (8848.03925 8027.90351)))
("SF_SOLAR" 0 ((8846.15385 8107.08891) (8872.54808 8099.84367) (8887.63292 8103.31176) (9027.60023 8103.62104)
(9038.46154 8099.54751)))
("SF_SOLAR" 0 ((8846.15385 7877.07387) (8853.69627 7877.07387)))
("SF_ARCHITECTURE" 0 ((8861.23586 3846.15385) (8849.92364 3849.92500)))
("SF_ARCHITECTURE" 0 ((8853.69627 3865.00713) (8849.92364 3861.23722) (8849.92364 3849.92500)))
("SF_ARCHITECTURE" 0 ((8861.23586 3846.15385) (8860.03247 3834.84163) (8849.92364 3823.52941)))
("SF_SOLAR" 0 ((8853.69536 8141.02568) (9019.60690 8141.02568)))
("SF_SOLAR" 1 ((8853.69536 8141.02568) (8855.58066 8133.48416) (8853.69536 8131.59876) (8851.80995 8133.48416)))
("SF_SOLAR" 0 ((8853.69627 8027.90351) (8861.23586 8027.90351)))
("SF_ARCHITECTURE" 0 ((8853.69627 4577.67681) (8930.16629 4698.34129) (8978.13066 4766.21459)))
("SF_ARCHITECTURE" 0 ((8951.73360 3978.12930) (8918.99559 3932.88043) (8875.26980 3861.23722) (8861.23586 3846.15385)))
("SF_SOLAR" 0 ((8865.00848 7990.19615) (8880.09050 7990.19615)))
("SF_SOLAR" 0 ((8868.77828 8118.40113) (8865.00848 8122.17195) (8868.77828 8129.71335)))
("SF_SOLAR" 0 ((8868.77828 8061.84016) (9059.19966 8061.84016)))
("SF_SOLAR" 0 ((9072.39819 8027.90351) (8876.32070 8027.90351)))
("SF_SOLAR" 0 ((8876.32070 8027.90351) (8886.73665 7997.74423) (8895.17251 7990.19615)))
("SF_SOLAR" 0 ((8880.09050 7922.32274) (8883.86029 7948.71799)))
("SF_SOLAR" 0 ((8895.17251 7948.71799) (8883.86029 7948.71799)))
("SF_SOLAR" 0 ((8891.40271 8069.38167) (8895.17251 8080.69389)))
("SF_SOLAR" 0 ((8891.40271 7873.30317) (8974.35803 7877.07387)))
("SF_SOLAR" 0 ((8895.17251 8122.17195) (8895.17251 8133.48416)))
("SF_SOLAR" 0 ((8895.17251 8046.75724) (8895.17251 8039.21561)))
("SF_SOLAR" 0 ((9110.10464 7948.71799) (9076.16799 7952.48213) (9053.54355 7948.72455) (9023.37952 7952.48869)
(8944.19400 7952.48213) (8925.33937 7948.87262) (8907.68337 7960.03676) (8895.17251 7990.19615)))
("SF_SOLAR" 0 ((9087.48020 7993.96674) (8914.02715 7993.96018) (8895.17251 7990.19615)))
("SF_ARCHITECTURE" 0 ((9034.69174 4909.50226) (8898.94514 4720.96572)))
("SF_ARCHITECTURE" 0 ((8906.48473 2175.71618) (8917.79695 2161.83767) (8936.64468 2160.78122) (8944.19400 2164.40396)))
("SF_ARCHITECTURE" 0 ((8906.48473 2175.71618) (8914.03405 2179.33971) (8936.50317 2178.28326) (8944.19400 2164.40396)))
("SF_SOLAR" 0 ((8914.02715 7922.32274) (8914.02715 7941.17647)))
("SF_SOLAR" 0 ((8917.79695 8118.40113) (8917.79695 8133.48416)))
("SF_SOLAR" 0 ((8917.79695 8035.44502) (8917.79695 8046.75724)))
("SF_SOLAR" 0 ((8917.79695 8016.59118) (8917.79695 8001.50837)))
("SF_ARCHITECTURE" 0 ((8917.79695 788.08541) (8925.33937 788.08541)))
("SF_SOLAR" 0 ((8925.33937 8088.23529) (8929.10916 8069.38167)))
("SF_SOLAR" 0 ((8940.42138 8125.94276) (8940.42138 8118.40113)))
("SF_SOLAR" 0 ((8940.42138 8039.21561) (8940.42138 8046.75724)))
("SF_SOLAR" 0 ((8940.42138 8012.82059) (8940.42138 8005.27896)))
("SF_SOLAR" 0 ((8940.42138 7978.88394) (8940.42138 7963.80090)))
("SF_ARCHITECTURE" 0 ((8955.50622 2164.40396) (8944.19400 2164.40396)))
("SF_ARCHITECTURE" 0 ((8944.19400 1289.59276) (8961.84864 1312.21719) (9013.11606 1398.78982) (9026.09989 1406.64005)
(9050.83009 1451.73360) (9113.87726 1538.46154)))
("SF_ARCHITECTURE" 0 ((8944.19400 788.08541) (8955.50622 791.84898) (9083.71041 791.85520)))
("SF_ARCHITECTURE" 0 ((8951.73450 7635.74661) (8951.73450 7571.64400)))
("SF_ARCHITECTURE" 0 ((8951.73450 7635.74661) (8959.42443 7653.40260) (8978.13066 7658.36448) (9000.75509 7654.60690)
(9709.65215 7654.59378) (9719.90871 7650.67489) (9724.73699 7635.74661)))
("SF_ARCHITECTURE" 0 ((8951.73450 6561.08597) (8951.73450 7571.64400)))
("SF_ARCHITECTURE" 0 ((8951.73450 6561.08597) (8959.28292 6557.46335) (9004.52489 6557.31550)))
("SF_ARCHITECTURE" 0 ((8955.50622 2164.40396) (8963.05339 2150.52545) (8978.12308 2149.46900) (8985.67025 2153.09174)))
("SF_ARCHITECTURE" 0 ((8955.50622 2164.40396) (8963.05339 2168.02749) (8977.98224 2166.97104) (8985.67025 2153.09174)))
("SF_SOLAR" 0 ((8963.04581 8118.40113) (8959.27602 8133.48416)))
("SF_SOLAR" 0 ((8959.27602 8092.00611) (8963.04581 8069.38167)))
("SF_SOLAR" 0 ((8963.04581 8039.21561) (8963.04581 8046.75724)))
("SF_SOLAR" 0 ((8963.04581 7963.80090) (8963.04581 7982.65452)))
("SF_SOLAR" 0 ((8985.67025 8174.96222) (8981.90045 8182.50385)))
("SF_SOLAR" 0 ((8985.67025 8035.44502) (8985.67025 8046.75724)))
("SF_SOLAR" 0 ((8985.67025 8016.59118) (8985.67025 8001.50837)))
("SF_ARCHITECTURE" 0 ((8985.67025 2153.09174) (9057.31618 2130.46731)))
("SF_SOLAR" 0 ((8989.44287 7877.07387) (9023.37952 7877.07387)))
("SF_SOLAR" 0 ((8993.21267 7967.57172) (8993.21267 7978.88394)))
("SF_SOLAR" 0 ((8996.98247 8133.48416) (8996.98247 8122.17195) (9000.75509 8118.40113)))
("SF_ARCHITECTURE" 0 ((8996.98247 1474.35803) (9031.97002 1534.69174) (9053.54355 1549.77376)))
("SF_ARCHITECTURE" 0 ((9004.52489 6557.31550) (9005.72975 7594.26844) (9015.83710 7604.37636) (9656.86369 7605.57410)
(9668.02059 7601.65532) (9671.93880 7590.49774) (9675.71640 6934.38914) (9668.17590 6900.45249) (9675.71640
6877.82805)))
("SF_ARCHITECTURE" 0 ((9004.52489 6557.31550) (9102.56505 6557.32206) (9113.87726 6561.08597)))
("SF_SOLAR" 0 ((9015.83710 8084.46448) (9019.60690 8073.15226)))
("SF_SOLAR" 0 ((9019.60690 8174.96222) (9016.13326 8182.51041) (9019.60690 8197.58665)))
("SF_SOLAR" 0 ((9030.91912 8005.27896) (9030.91912 8012.82059)))
("SF_SOLAR" 0 ((9030.91912 7982.65452) (9030.91912 7967.57172)))
("SF_SOLAR" 0 ((9030.91912 7926.09355) (9030.91912 7933.63495)))
("SF_SOLAR" 0 ((9034.69174 8039.21561) (9034.69174 8046.75724)))
("SF_SOLAR" 0 ((9053.54355 8141.02568) (9042.23133 8141.02568)))
("SF_ARCHITECTURE" 0 ((9053.54355 1549.77376) (9052.49480 1530.91912) (9042.23133 1512.06731)))
("SF_SOLAR" 0 ((9064.85577 8129.71335) (9049.77376 8122.17195)))
("SF_SOLAR" 0 ((9049.77376 8012.82059) (9049.77376 8005.27896)))
("SF_ARCHITECTURE" 0 ((9053.54355 5109.35102) (9072.24355 5108.15373) (9076.16799 5101.80995)))
("SF_ARCHITECTURE" 0 ((9053.54355 5109.35102) (9058.36493 5094.42285) (9064.85577 5090.49774)))
("SF_ARCHITECTURE" 0 ((9083.71041 1602.56505) (9053.54355 1549.77376)))
("SF_SOLAR" 0 ((9072.39819 8103.31833) (9057.31618 8099.54751)))
("SF_ARCHITECTURE" 0 ((9057.31618 4264.70588) (9068.62839 4275.86346) (9079.94061 4274.96143) (9091.25283 4268.47704)))
("SF_ARCHITECTURE" 0 ((9085.59672 2117.27025) (9065.00419 2116.58880) (9057.31618 2130.46731)))
("SF_ARCHITECTURE" 0 ((9085.59672 2117.27025) (9076.02093 2133.03371) (9057.31618 2130.46731)))
("SF_SOLAR" 0 ((9066.74208 8061.84016) (9064.85577 8061.84016) (9061.08597 8061.84016) (9059.19966 8061.84016)))
("SF_SOLAR" 0 ((9276.01810 8167.42081) (9264.70588 8163.65656) (9042.23133 8166.36448) (9032.12398 8159.73122)
(9031.07443 8133.48416) (9044.95373 8107.08891) (9059.19966 8061.84016)))
("SF_SOLAR" 0 ((9061.08597 7982.65452) (9064.85577 7967.57172)))
("SF_SOLAR" 0 ((9064.85577 8156.10860) (9064.85577 8129.71335)))
("SF_SOLAR" 0 ((9064.85577 8129.71335) (9074.97081 8122.16527) (9083.71041 8103.31833)))
("SF_ARCHITECTURE" 0 ((9064.85577 5090.49774) (9068.78167 5080.23495) (9117.49242 5037.70781) (9121.41776 5022.62443)
(9132.72907 5011.31222)))
("SF_ARCHITECTURE" 0 ((9064.85577 5090.49774) (9076.16799 5101.80995)))
("SF_SOLAR" 0 ((9298.64253 8061.84016) (9287.33032 8061.84016) (9066.74208 8061.84016)))
("SF_SOLAR" 0 ((9072.39819 8027.90351) (9065.07885 8050.59525) (9066.74208 8061.84016)))
("SF_SOLAR" 0 ((9072.39819 8141.02568) (9272.24830 8141.02568)))
("SF_SOLAR" 0 ((9087.48020 7993.96674) (9072.39819 8027.90351)))
("SF_SOLAR" 0 ((9076.16799 7929.86425) (9076.16799 7941.17647)))
("SF_ARCHITECTURE" 0 ((9076.16799 5101.80995) (9125.18948 5067.72523) (9142.83790 5049.02002) (9143.88801 5026.39559)
(9132.72907 5011.31222)))
("SF_ARCHITECTURE" 0 ((9076.16799 1610.10464) (9076.16799 1606.33484) (9083.71041 1602.56505)))
("SF_SOLAR" 0 ((9287.33032 8099.54751) (9276.01810 8103.31176) (9083.71041 8103.31833)))
("SF_SOLAR" 0 ((9091.25283 8069.38167) (9083.71041 8103.31833)))
("SF_SOLAR" 0 ((9083.71041 8027.90351) (9106.33484 8027.90351)))
("SF_ARCHITECTURE" 0 ((9091.25283 3329.56233) (9083.71041 3322.02138)))
("SF_ARCHITECTURE" 0 ((9083.71041 1602.56505) (9098.79242 1617.64706)))
("SF_ARCHITECTURE" 0 ((9085.59672 2117.27025) (9095.16765 2105.27998) (9113.87726 2100.30192)))
("SF_ARCHITECTURE" 0 ((9085.59672 2117.27025) (9098.79038 2122.62670) (9109.95136 2118.10566) (9113.87726 2111.61414)))
("SF_SOLAR" 0 ((9087.48020 7993.96674) (9091.25283 7990.19615)))
("SF_SOLAR" 0 ((9087.48020 7993.96674) (9087.48020 7990.19615) (9091.25283 7990.19615)))
("SF_SOLAR" 0 ((9087.48020 7877.07387) (9102.56505 7877.07387)))
("SF_ARCHITECTURE" 0 ((9087.48020 1632.72907) (9098.79242 1617.64706)))
("SF_SOLAR" 0 ((9091.25283 7990.19615) (9102.56505 7960.03020)))
("SF_SOLAR" 0 ((9091.25283 7990.19615) (9098.80000 7993.81878) (9128.95928 7993.96674)))
("SF_SOLAR" 0 ((9098.79242 8122.17195) (9098.79242 8133.48416)))
("SF_SOLAR" 0 ((9098.79242 8050.52783) (9106.33484 8027.90351)))
("SF_ARCHITECTURE" 0 ((9110.10464 1640.27149) (9108.90124 1628.95928) (9098.79242 1617.64706)))
("SF_ARCHITECTURE" 0 ((9102.56505 1647.81391) (9110.10464 1640.27149)))
("SF_SOLAR" 0 ((9306.18495 8027.90351) (9121.41686 8027.90351) (9106.33484 8027.90351)))
("SF_SOLAR" 0 ((9110.10464 7948.71799) (9336.34898 7948.71799)))
("SF_SOLAR" 0 ((9110.10464 7948.71799) (9110.10464 7926.09355)))
("SF_ARCHITECTURE" 0 ((9110.10464 1640.27149) (9127.90294 1659.12613) (9176.77455 1738.31165) (9177.97794 1749.62387)))
("SF_SOLAR" 0 ((9121.41686 8001.50837) (9113.87726 8020.36199)))
("SF_ARCHITECTURE" 0 ((9155.35351 6866.51584) (9113.87726 6866.51584)))
("SF_ARCHITECTURE" 0 ((9113.87726 6866.51584) (9113.87726 6561.08597)))
("SF_ARCHITECTURE" 0 ((9113.87726 6866.51584) (9115.08066 7488.68122) (9128.95928 7496.22296) (9294.87274 7496.23609)
(9317.49717 7500.00000) (9347.66120 7496.22952)))
("SF_ARCHITECTURE" 0 ((9147.81391 6561.08597) (9132.72907 6557.31550) (9113.87726 6561.08597)))
("SF_ARCHITECTURE" 0 ((9113.87726 4407.99355) (9121.42443 4400.60713) (9140.26459 4400.60713) (9146.60147 4404.37760)
(9142.83790 4438.15339) (9132.72907 4445.70136)))
("SF_ARCHITECTURE" 0 ((9113.87726 4407.99355) (9121.41776 4434.38914) (9132.72907 4445.70136)))
("SF_ARCHITECTURE" 0 ((9140.27149 2100.30192) (9136.34638 2106.65192) (9113.87726 2111.61414)))
("SF_ARCHITECTURE" 0 ((9113.87726 2111.61414) (9113.87726 2100.30192)))
("SF_ARCHITECTURE" 0 ((9140.27149 2088.98971) (9117.80170 2093.95735) (9113.87726 2100.30192)))
("SF_SOLAR" 0 ((9121.41686 8133.48416) (9121.41686 8118.40113)))
("SF_SOLAR" 0 ((9121.41686 8069.38167) (9121.41686 8084.46448)))
("SF_SOLAR" 0 ((9317.49717 7993.96674) (9128.95928 7993.96674)))
("SF_SOLAR" 0 ((9136.50170 7960.03020) (9128.95928 7993.96674)))
("SF_ARCHITECTURE" 0 ((9132.72907 4445.70136) (9132.72907 5011.31222)))
("SF_ARCHITECTURE" 0 ((9140.27149 2100.30192) (9155.34864 2097.42624) (9162.89593 2088.98971)))
("SF_ARCHITECTURE" 0 ((9140.27149 2088.98971) (9140.27149 2100.30192)))
("SF_ARCHITECTURE" 0 ((9140.27149 2088.98971) (9144.19661 2082.63903) (9159.12613 2077.67749)))
("SF_SOLAR" 0 ((9144.04129 8039.21561) (9144.04129 8050.52783)))
("SF_SOLAR" 0 ((9144.04129 7941.17647) (9147.81391 7926.09355)))
("SF_SOLAR" 0 ((9147.81391 8016.59118) (9147.81391 8005.27896)))
("SF_ARCHITECTURE" 0 ((9347.66120 7469.83382) (9332.57919 7462.44729) (9253.39367 7465.91505) (9242.08145 7462.44072)
(9166.66572 7462.14457) (9147.81391 7454.75113)))
("SF_ARCHITECTURE" 0 ((9475.86821 6557.31550) (9159.12613 6557.32206) (9147.81391 6561.08597)))
("SF_ARCHITECTURE" 0 ((9147.81391 6561.08597) (9147.96097 6806.18428) (9159.12613 6836.34966)))
("SF_SOLAR" 0 ((9155.35351 8133.48416) (9155.35351 8118.40113)))
("SF_SOLAR" 0 ((9155.35351 8069.38167) (9155.35351 8084.46448)))
("SF_ARCHITECTURE" 0 ((9155.35351 6866.51584) (9204.37500 6862.74536)))
("SF_ARCHITECTURE" 0 ((9155.35351 6866.51584) (9155.50192 6843.89796) (9159.12613 6836.34966)))
("SF_ARCHITECTURE" 0 ((9155.35351 818.24943) (9181.74299 813.27477) (9188.08676 806.93235) (9189.14310 791.85520)
(9184.31550 773.00057) (9174.20814 761.68835)))
("SF_ARCHITECTURE" 0 ((9155.35351 818.24943) (9155.50882 791.85520) (9162.89593 780.54299)))
("SF_ARCHITECTURE" 0 ((9155.35351 818.24943) (9113.87726 814.48586) (8944.19400 817.05226) (8902.71493 814.33122)
(8888.68857 806.79016) (8883.86719 791.85520) (8884.01561 441.17647) (8887.78620 433.78247) (8902.71493 426.24219)
(9170.43835 426.24219) (9181.59525 430.92059) (9185.36572 437.41154) (9185.36572 467.57070) (9174.20814 482.65554)))
("SF_ARCHITECTURE" 0 ((9174.20814 482.65554) (9166.80803 478.72964) (9155.35351 460.03111)))
("SF_ARCHITECTURE" 0 ((9204.37500 6840.12093) (9193.06278 6836.49796) (9159.12613 6836.34966)))
("SF_ARCHITECTURE" 0 ((9159.12613 2077.67749) (9181.75057 2066.36527)))
("SF_ARCHITECTURE" 0 ((9159.12613 2077.67749) (9162.89593 2088.98971)))
("SF_ARCHITECTURE" 0 ((9185.52036 2077.67749) (9177.97308 2086.11403) (9162.89593 2088.98971)))
("SF_ARCHITECTURE" 0 ((9162.89593 780.54299) (9170.43835 776.77319) (9170.43835 773.00057)))
("SF_ARCHITECTURE" 0 ((9162.89593 780.54299) (9166.66572 773.00057) (9170.43835 773.00057)))
("SF_SOLAR" 0 ((9166.66572 8050.52783) (9166.66572 8039.21561)))
("SF_SOLAR" 0 ((9166.66572 7982.65452) (9170.43835 7963.80090)))
("SF_ARCHITECTURE" 0 ((9170.43835 7432.12670) (9156.55837 7420.80792) (9151.58371 7386.87783) (9155.34106 7334.08722)
(9151.58993 7315.23405) (9151.58371 7077.67749) (9155.34864 7055.05305) (9155.36109 6915.53518) (9159.27941 6904.37783)
(9170.43835 6900.45905) (9487.18043 6900.45905) (9497.43552 6904.37783) (9506.02738 6930.61867) (9506.03914 7337.85848)
(9509.80486 7360.48292) (9506.03224 7420.81448)))
("SF_ARCHITECTURE" 0 ((9291.10011 3273.00124) (9189.29016 3273.14977) (9170.43835 3284.31346)))
("SF_ARCHITECTURE" 0 ((9170.43835 3284.31346) (9170.44321 4125.18812) (9174.20192 4144.04265) (9174.21437 4298.64253)
(9177.83088 4313.72590) (9177.97794 4355.20362)))
("SF_ARCHITECTURE" 0 ((9174.20814 761.68835) (9170.43835 773.00057)))
("SF_ARCHITECTURE" 0 ((9174.20814 761.68835) (9174.20814 482.65554)))
("SF_SOLAR" 0 ((9189.29016 7971.34231) (9177.97794 7971.34231)))
("SF_ARCHITECTURE" 0 ((9181.75057 3110.85973) (9211.91459 3140.87738) (9241.93303 3163.65034) (9272.24830 3216.44016)))
("SF_ARCHITECTURE" 0 ((9200.60238 2055.05305) (9185.67500 2060.01459) (9181.75057 2066.36527)))
("SF_ARCHITECTURE" 0 ((9185.52036 2077.67749) (9181.75057 2066.36527)))
("SF_SOLAR" 0 ((9189.29016 8114.63054) (9185.52036 8133.48416)))
("SF_ARCHITECTURE" 0 ((9185.52036 2077.67749) (9200.44910 2072.85679) (9204.37500 2066.36527)))
("SF_SOLAR" 0 ((9189.29016 8088.23529) (9189.29016 8069.38167)))
("SF_SOLAR" 0 ((9189.29016 8005.27896) (9189.29016 8016.59118)))
("SF_SOLAR" 0 ((9189.29016 7971.34231) (9189.29016 7986.42534)))
("SF_SOLAR" 0 ((9204.37500 7971.34231) (9189.29016 7971.34231)))
("SF_ARCHITECTURE" 0 ((9211.91459 7435.89717) (9196.83948 7429.55373) (9189.29016 7432.12670)))
("SF_SOLAR" 0 ((9193.06278 8039.21561) (9193.06278 8046.75724)))
("SF_ARCHITECTURE" 0 ((9309.95475 6753.39367) (9200.60238 6757.16414)))
("SF_ARCHITECTURE" 0 ((9358.97342 6681.74989) (9208.15170 6681.90430) (9200.60238 6689.29084)))
("SF_ARCHITECTURE" 0 ((9200.60238 6606.33484) (9242.08145 6610.10532) (9283.56052 6609.95747) (9298.64253 6606.33484)))
("SF_ARCHITECTURE" 0 ((9200.60238 2055.05305) (9208.15170 2048.70238) (9226.99943 2043.74084)))
("SF_ARCHITECTURE" 0 ((9200.60238 2055.05305) (9204.37500 2066.36527)))
("SF_ARCHITECTURE" 0 ((9204.37500 6840.12093) (9204.37500 6862.74536)))
("SF_ARCHITECTURE" 0 ((9204.37500 6862.74536) (9219.45701 6866.50928) (9358.97342 6862.74536) (9426.84672 6866.51584)))
("SF_ARCHITECTURE" 0 ((9204.37500 6840.12093) (9211.92217 6836.49796) (9291.10011 6836.20181) (9302.41233 6828.80848)
(9328.80939 6828.80848) (9366.51584 6828.80848)))
("SF_ARCHITECTURE" 0 ((9204.37500 2066.36527) (9219.30860 2061.53767) (9226.99943 2043.74084)))
("SF_ARCHITECTURE" 0 ((9347.66120 6708.14480) (9309.95475 6719.30871) (9208.14480 6719.45701)))
("SF_ARCHITECTURE" 0 ((9298.64253 6640.27149) (9208.14480 6640.27149)))
("SF_SOLAR" 0 ((9211.91459 8050.52783) (9211.91459 8039.21561)))
("SF_SOLAR" 0 ((9219.45701 8133.48416) (9215.68722 8118.40113)))
("SF_SOLAR" 0 ((9219.45701 7971.34231) (9215.68722 7982.65452)))
("SF_SOLAR" 0 ((9215.68722 7960.03020) (9215.68722 7971.34231) (9219.45701 7971.34231)))
("SF_SOLAR" 0 ((9219.45701 8005.27896) (9219.45701 8020.36199)))
("SF_SOLAR" 0 ((9219.45701 7971.34231) (9242.08145 7971.34231)))
("SF_SOLAR" 0 ((9226.99943 8084.46448) (9226.99943 8073.15226)))
("SF_SOLAR" 0 ((9226.99943 7926.09355) (9230.76923 7937.40577)))
("SF_ARCHITECTURE" 0 ((9226.99943 2043.74084) (9257.16346 2028.65735)))
("SF_SOLAR" 0 ((9242.08145 8182.50385) (9242.08145 8174.96222)))
("SF_ARCHITECTURE" 0 ((9242.08145 7428.35622) (9249.62873 7431.97839) (9298.64253 7432.12670)))
("SF_ARCHITECTURE" 0 ((9245.85124 7021.11640) (9290.05136 7088.98971) (9337.54762 7175.71618) (9385.37048 7243.58948)))
("SF_SOLAR" 0 ((9253.39367 8118.40113) (9253.39367 8133.48416)))
("SF_SOLAR" 0 ((9264.70588 7971.34231) (9253.62081 7971.71086) (9253.39367 7982.65452)))
("SF_ARCHITECTURE" 0 ((9276.01810 2009.80419) (9264.85362 2014.63100) (9257.16346 2028.65735)))
("SF_ARCHITECTURE" 0 ((9279.78790 2021.11640) (9268.47568 2031.36527) (9257.16346 2028.65735)))
("SF_SOLAR" 0 ((9272.24830 8231.52330) (9268.47568 8223.98190)))
("SF_SOLAR" 0 ((9268.47568 8069.38167) (9268.47568 8084.46448)))
("SF_ARCHITECTURE" 0 ((9291.10011 3273.00124) (9298.48790 3261.68903) (9297.43767 3227.75238) (9287.33032 3217.64434)
(9272.24830 3216.44016)))
("SF_SOLAR" 0 ((9276.01810 8167.42081) (9308.89842 8061.84016) (9314.78167 8027.90351) (9331.52285 7978.88394)
(9336.34898 7948.71799)))
("SF_SOLAR" 0 ((9276.01810 8167.42081) (9279.78790 8193.81606)))
("SF_SOLAR" 0 ((9276.01810 8050.52783) (9276.01810 8039.21561)))
("SF_ARCHITECTURE" 0 ((9291.10011 1998.49197) (9283.56052 1999.69604) (9276.01810 2009.80419)))
("SF_ARCHITECTURE" 0 ((9279.78790 2021.11640) (9276.01810 2009.80419)))
("SF_SOLAR" 0 ((9321.26697 7869.53247) (9317.79265 7877.37002) (9279.78790 7877.07387)))
("SF_ARCHITECTURE" 0 ((9298.64253 2006.03292) (9294.71742 2013.43314) (9279.78790 2021.11640)))
("SF_SOLAR" 0 ((9287.33032 8020.36199) (9287.33032 8005.27896)))
("SF_ARCHITECTURE" 0 ((9313.72455 1979.63801) (9295.02602 1988.23541) (9291.10011 1998.49197)))
("SF_ARCHITECTURE" 0 ((9298.64253 2006.03292) (9294.87274 2006.03292) (9291.10011 1998.49197)))
("SF_SOLAR" 0 ((9302.41233 8174.96222) (9294.87274 8171.19163)))
("SF_SOLAR" 0 ((9298.64253 7963.80090) (9294.87274 7982.65452)))
("SF_ARCHITECTURE" 0 ((9294.87274 7160.63348) (9393.96719 7322.77500) (9411.76471 7345.39943)))
("SF_ARCHITECTURE" 0 ((9294.87274 999.24491) (9309.95475 991.71776) (9323.83337 999.25249) (9324.88348 1021.86934)
(9317.49717 1033.18156)))
("SF_ARCHITECTURE" 0 ((9294.87274 999.24491) (9302.41324 1025.63439) (9317.49717 1033.18156)))
("SF_ARCHITECTURE" 0 ((9298.64253 2006.03292) (9308.89842 2002.10781) (9313.72455 1979.63801)))
("SF_SOLAR" 0 ((9306.18495 8223.98190) (9302.41233 8231.52330)))
("SF_SOLAR" 0 ((9325.03676 8163.65000) (9314.78167 8174.96233) (9306.18495 8193.81606)))
("SF_ARCHITECTURE" 0 ((9313.72455 7428.35622) (9392.91007 7428.50407) (9411.76471 7432.12670) (9457.01357 7428.36934)
(9472.09559 7431.83088) (9506.03224 7420.81448)))
("SF_ARCHITECTURE" 0 ((9313.72455 1979.63801) (9317.49027 1968.32579) (9313.72455 1082.20305) (9317.49717 1033.18156)))
("SF_ARCHITECTURE" 0 ((9321.26697 935.14423) (9325.03676 916.28959) (9325.03190 252.63857) (9321.26697 241.32636)))
("SF_ARCHITECTURE" 0 ((9392.91097 237.55656) (9343.89140 233.93382) (9321.26697 241.32636)))
("SF_SOLAR" 0 ((9506.03224 8163.65000) (9325.03676 8163.65000)))
("SF_SOLAR" 0 ((9325.03676 8163.65000) (9329.86505 8125.94276) (9351.43382 8061.84005)))
("SF_ARCHITECTURE" 0 ((9404.22229 6636.50102) (9389.14027 6640.26493) (9332.58609 6636.64887) (9325.03676 6640.27149)))
("SF_ARCHITECTURE" 0 ((9332.57919 6613.87658) (9343.89140 6610.10532)))
("SF_SOLAR" 0 ((9336.34898 8141.02557) (9355.20362 8144.50023) (9370.28563 8141.03213) (9457.01357 8141.03213)
(9472.09559 8144.50023) (9494.72002 8141.03213) (9509.80486 8144.79638)))
("SF_SOLAR" 0 ((9347.66120 7919.80894) (9346.60554 7929.77229) (9336.34898 7948.71799)))
("SF_ARCHITECTURE" 0 ((9358.97342 2156.86301) (9355.04898 2163.21301) (9340.12161 2168.17523)))
("SF_ARCHITECTURE" 0 ((9358.97342 2156.86301) (9347.66120 2150.68009) (9341.32500 2156.86923) (9340.12161 2168.17523)))
("SF_SOLAR" 0 ((9347.66120 8182.50385) (9347.66120 8174.96222)))
("SF_SOLAR" 0 ((9347.66120 8107.08891) (9419.30713 8099.55407) (9483.40781 8099.69548) (9498.49265 8103.30520)
(9513.57466 8099.84367) (9524.88688 8103.31833)))
("SF_ARCHITECTURE" 0 ((9347.66120 7496.22952) (9347.66120 7469.83382)))
("SF_ARCHITECTURE" 0 ((9347.66120 7496.22952) (9385.37048 7500.00000) (9407.99491 7496.23609) (9543.74152 7496.22296)
(9562.59423 7488.68122) (9558.81663 6934.38914) (9551.28111 6915.53518)))
("SF_ARCHITECTURE" 0 ((9524.88688 7420.81448) (9523.68201 7450.97410) (9509.80486 7461.23609) (9366.51584 7462.44072)
(9347.66120 7469.83382)))
("SF_SOLAR" 0 ((9532.42930 8061.84005) (9351.43382 8061.84005)))
("SF_SOLAR" 0 ((9385.37048 7922.32274) (9351.43382 8061.84005)))
("SF_SOLAR" 0 ((9355.20362 7895.92760) (9362.74604 7861.99095)))
("SF_ARCHITECTURE" 0 ((9358.97342 2156.86301) (9370.28077 2155.65882) (9377.82805 2145.55079)))
("SF_SOLAR" 0 ((9370.28563 8118.40113) (9362.74604 8133.48416)))
("SF_SOLAR" 0 ((9366.51584 8027.90339) (9539.96889 8027.90339)))
("SF_ARCHITECTURE" 0 ((9407.99491 6753.39367) (9385.37048 6758.22093) (9371.49050 6768.48292) (9366.51584 6828.80848)))
("SF_ARCHITECTURE" 0 ((9366.51584 6828.80848) (9426.84672 6836.34966)))
("SF_ARCHITECTURE" 0 ((9370.28563 2138.00905) (9377.82805 2145.55079)))
("SF_SOLAR" 0 ((9374.05826 8088.23529) (9374.05826 8073.15226)))
("SF_SOLAR" 0 ((9377.82805 7993.96674) (9539.96889 7993.96674)))
("SF_SOLAR" 0 ((9404.22229 7858.22025) (9397.87296 7865.76833) (9391.70667 7888.38609) (9377.82805 7907.23982)))
("SF_SOLAR" 0 ((9385.37048 7922.32274) (9377.82805 7907.23982)))
("SF_ARCHITECTURE" 0 ((9411.76471 2122.92636) (9392.91007 2140.72319) (9377.82805 2145.55079)))
("SF_SOLAR" 0 ((9385.37048 7922.32274) (9411.76471 7911.01052) (9977.37557 7911.01052)))
("SF_ARCHITECTURE" 0 ((9389.14027 6610.10532) (9423.07692 6606.33484)))
("SF_ARCHITECTURE" 0 ((9392.91097 237.55656) (9392.91097 211.16233) (9392.91097 188.53790)))
("SF_ARCHITECTURE" 0 ((9498.49174 188.53790) (9483.40781 184.76527) (9404.22229 184.91369) (9392.91097 188.53790)))
("SF_SOLAR" 0 ((9396.68269 8016.59118) (9396.68269 8001.50837)))
("SF_SOLAR" 0 ((9562.59333 7948.71799) (9528.65667 7952.48869) (9411.76471 7952.48213) (9396.68269 7948.71799)))
("SF_ARCHITECTURE" 0 ((9396.68269 2115.38462) (9404.22229 2115.38462)))
("SF_ARCHITECTURE" 0 ((9415.53450 2104.07240) (9411.76471 2104.07240) (9404.22229 2115.38462)))
("SF_ARCHITECTURE" 0 ((9411.76471 2122.92636) (9404.22229 2115.38462)))
("SF_SOLAR" 0 ((9407.99491 7967.57172) (9407.99491 7982.65452)))
("SF_ARCHITECTURE" 0 ((9445.70136 6704.37410) (9426.84672 6704.37410) (9416.59163 6712.06357) (9408.14197 6738.31097)
(9407.99491 6753.39367)))
("SF_ARCHITECTURE" 0 ((9407.99491 6753.39367) (9415.54208 6757.01629) (9468.32579 6760.92885) (9762.44344 6760.92885)
(9781.29808 6757.17070) (10599.54751 6757.16414)))
("SF_ARCHITECTURE" 0 ((9411.76471 2122.92636) (9415.53450 2122.92636) (9423.07692 2111.61414)))
("SF_ARCHITECTURE" 0 ((9415.53450 2104.07240) (9423.07692 2093.96437) (9430.61934 2092.76018)))
("SF_ARCHITECTURE" 0 ((9415.53450 2104.07240) (9423.07692 2111.61414)))
("SF_ARCHITECTURE" 0 ((9438.15894 2100.30192) (9430.61934 2110.40995) (9423.07692 2111.61414)))
("SF_SOLAR" 0 ((9426.84672 8133.48416) (9426.84672 8122.17195)))
("SF_SOLAR" 0 ((9426.84672 8080.69389) (9426.84672 8088.23529)))
("SF_ARCHITECTURE" 0 ((9472.09559 6847.66188) (9457.01357 6865.31154) (9426.84672 6866.51584)))
("SF_ARCHITECTURE" 0 ((9426.84672 6866.51584) (9426.84672 6836.34966)))
("SF_ARCHITECTURE" 0 ((9472.09559 6847.66188) (9457.01357 6836.50452) (9426.84672 6836.34966)))
("SF_ARCHITECTURE" 0 ((9453.24378 2077.67749) (9438.16652 2082.50430) (9430.61934 2092.76018)))
("SF_ARCHITECTURE" 0 ((9438.15894 2100.30192) (9430.61934 2092.76018)))
("SF_ARCHITECTURE" 0 ((9438.15894 2100.30192) (9445.70758 2099.09774) (9457.01357 2088.98971)))
("SF_ARCHITECTURE" 0 ((10565.61086 6700.60305) (10546.75622 6708.13824) (9460.78337 6704.37410) (9445.70136
6704.37410)))
("SF_ARCHITECTURE" 0 ((9475.86821 6557.31550) (9475.71980 6636.50102) (9450.52828 6681.74989) (9445.70136 6704.37410)))
("SF_SOLAR" 0 ((9449.47115 8035.44502) (9449.47115 8046.75724)))
("SF_SOLAR" 0 ((9453.24378 7971.34231) (9449.47115 7978.88394)))
("SF_ARCHITECTURE" 0 ((9453.24378 2077.67749) (9460.78428 2055.05305)))
("SF_ARCHITECTURE" 0 ((9457.01357 2088.98971) (9453.24378 2077.67749)))
("SF_ARCHITECTURE" 0 ((9453.24378 810.70984) (9453.24378 784.31278)))
("SF_ARCHITECTURE" 0 ((9453.24378 607.08993) (9453.24378 739.06391)))
("SF_ARCHITECTURE" 0 ((9453.24378 444.94627) (9453.24378 452.48869)))
("SF_ARCHITECTURE" 0 ((9453.24378 422.32183) (9453.24378 429.86425)))
("SF_ARCHITECTURE" 0 ((9453.24378 312.97229) (9453.24378 384.61538)))
("SF_ARCHITECTURE" 0 ((9457.01357 2088.98971) (9487.18043 2073.75158) (9497.28778 2062.59400) (9498.49174 188.53790)))
("SF_SOLAR" 0 ((9468.32579 8084.46448) (9472.09559 8073.15226)))
("SF_SOLAR" 0 ((9468.32579 7967.57172) (9468.32579 7978.88394)))
("SF_SOLAR" 0 ((9472.09559 8137.25498) (9472.09559 8118.40113)))
("SF_ARCHITECTURE" 0 ((9472.09559 6847.66188) (9490.95023 6847.66188)))
("SF_ARCHITECTURE" 0 ((9479.63801 6451.73462) (9475.86821 6557.31550)))
("SF_ARCHITECTURE" 0 ((9479.63801 6451.73462) (9494.72002 6447.97036) (9528.65181 6451.58654) (9536.19910 6447.96380)))
("SF_ARCHITECTURE" 0 ((9555.05373 6836.34966) (9539.96889 6828.80848) (9513.57466 6828.80848) (9490.95023 6847.66188)))
("SF_ARCHITECTURE" 0 ((9490.95023 6847.66188) (9506.03224 6861.68857) (9517.34446 6866.51584)))
("SF_SOLAR" 0 ((9494.72002 8088.23529) (9494.72002 8069.38167)))
("SF_ARCHITECTURE" 0 ((9539.96889 184.76527) (9498.49174 188.53790)))
("SF_SOLAR" 0 ((9498.49265 8039.21561) (9498.49265 8046.75724)))
("SF_SOLAR" 0 ((9506.03224 8163.65000) (9509.80486 8144.79638)))
("SF_SOLAR" 0 ((9506.03224 8163.65000) (9532.42930 8171.03032) (9547.51131 8159.87941)))
("SF_ARCHITECTURE" 0 ((9524.88688 7420.81448) (9506.03224 7420.81448)))
("SF_SOLAR" 0 ((9517.34446 8141.02557) (9509.80486 8144.79638)))
("SF_SOLAR" 0 ((9513.57466 8005.27896) (9513.57466 8016.59118)))
("SF_SOLAR" 0 ((9517.34446 8141.02557) (9539.96889 8141.02557)))
("SF_SOLAR" 0 ((9517.34446 8141.02557) (9517.34446 8118.40113)))
("SF_SOLAR" 0 ((9517.34446 7967.57172) (9517.34446 7978.88394)))
("SF_ARCHITECTURE" 0 ((9555.05373 6851.43314) (9547.50441 6857.77658) (9528.65667 6860.03054) (9517.34446 6866.51584)))
("SF_ARCHITECTURE" 0 ((9543.74152 6917.42081) (9533.48495 6904.22647) (9527.45328 6881.59853) (9517.34446 6866.51584)))
("SF_SOLAR" 0 ((9528.65667 8073.15226) (9524.88688 8103.31833)))
("SF_SOLAR" 0 ((9524.88688 8103.31833) (9526.08484 8114.62398) (9532.42930 8122.17195)))
("SF_ARCHITECTURE" 0 ((9536.19910 6926.84740) (9528.66425 6941.93088) (9528.65181 7311.46278) (9524.88688 7334.08722)
(9525.03462 7394.41957) (9528.64423 7409.50226) (9524.88688 7420.81448)))
("SF_SOLAR" 0 ((9547.51131 8099.54751) (9532.42930 8095.77670)))
("SF_SOLAR" 0 ((9532.42930 8061.84005) (9539.96889 8027.90339)))
("SF_SOLAR" 0 ((9543.74152 8065.61086) (9532.42930 8061.84005)))
("SF_SOLAR" 0 ((9536.19910 8197.58665) (9536.19910 8182.50385)))
("SF_ARCHITECTURE" 0 ((9536.19910 6926.84740) (9543.74152 6923.07692) (9543.74152 6917.42081)))
("SF_ARCHITECTURE" 0 ((9536.19910 6926.84740) (9543.74152 6917.42081)))
("SF_MASONRY_AND_ARCH" 0 ((9536.19910 6447.96380) (9536.19910 6195.32421)))
("SF_ARCHITECTURE" 0 ((9536.19910 6447.96380) (9555.05373 6451.73462) (10437.40667 6451.73450) (10448.71889
6451.73450)))
("SF_MASONRY_AND_ARCH" 0 ((9539.96889 5829.56267) (9536.20532 5882.35294) (9539.96889 5953.99706) (9536.20532
5976.62149) (9536.19910 6195.32421)))
("SF_SOLAR" 0 ((9558.82353 7960.03020) (9551.42952 7971.34242) (9547.36357 8005.27896) (9539.96889 8027.90339)))
("SF_MASONRY_AND_ARCH" 0 ((9539.96889 5829.56267) (9539.96889 5750.37715)))
("SF_MASONRY_AND_ARCH" 0 ((9539.96889 5607.08857) (9539.96889 5750.37715)))
("SF_MASONRY_AND_ARCH" 0 ((9539.96889 5607.08857) (9539.96889 2820.51256)))
("SF_MASONRY_AND_ARCH" 0 ((9539.96889 2820.51256) (9543.74152 2797.88812) (9540.11731 2779.03495) (9539.96889
2707.39038)))
("SF_MASONRY_AND_ARCH" 0 ((9539.96889 184.76527) (9539.96889 2707.39038)))
("SF_MASONRY_AND_ARCH" 0 ((9539.96889 124.43439) (9543.74152 143.28903) (9539.96889 184.76527)))
("SF_MASONRY_AND_ARCH" 0 ((9539.96889 124.43439) (9543.59310 116.88710) (9543.74152 67.87330)))
("SF_SOLAR" 0 ((9555.05373 8061.84005) (9543.74152 8065.61086)))
("SF_SOLAR" 0 ((9543.74152 8065.61086) (9543.74152 8073.15226) (9551.28111 8080.69389)))
("SF_ARCHITECTURE" 0 ((9543.74152 6917.42081) (9551.28111 6915.53518)))
("SF_MASONRY_AND_ARCH" 0 ((9543.74152 -3.77070) (9539.96889 18.85464) (9543.74152 67.87330)))
("SF_ARCHITECTURE" 0 ((9543.74152 -3.77070) (9562.59333 -3.77070) (9860.48360 -3.77070) (9883.10803 -3.77070)
(10395.92760 -3.77070) (10426.09446 -3.77070) (10448.71889 -3.77070)))
("SF_SOLAR" 0 ((9562.59333 8095.77670) (9555.20079 8114.63054) (9547.51131 8159.87941)))
("SF_SOLAR" 0 ((9713.42477 8167.42081) (9705.87545 8163.79808) (9558.82353 8163.64344) (9547.51131 8159.87941)))
("SF_SOLAR" 0 ((9551.28111 8027.90339) (9570.13575 8024.13281) (9577.67817 8020.36199) (9585.21776 7993.96674)))
("SF_ARCHITECTURE" 0 ((9555.05373 6851.43314) (9562.44005 6862.74536) (9562.44559 6896.68201) (9551.28111 6915.53518)))
("SF_ARCHITECTURE" 0 ((9555.05373 6836.34966) (9555.05373 6851.43314)))
("SF_ARCHITECTURE" 0 ((9555.05373 6836.34966) (9573.90554 6828.80848) (9709.65215 6828.80848) (9720.96437 6828.80848)))
("SF_SOLAR" 0 ((9713.42477 8144.79638) (9653.09106 8144.64842) (9638.00905 8141.03224) (9596.52998 8144.78982)
(9558.82353 8141.02557)))
("SF_SOLAR" 0 ((9585.21776 7993.96674) (9558.82353 7993.96674)))
("SF_SOLAR" 0 ((9562.59333 8095.77670) (9563.79819 8069.38824) (9570.14265 8063.03778) (9585.21776 8058.21742)
(9728.49989 8061.99480) (9734.84434 8069.38824) (9724.73699 8141.02557)))
("SF_SOLAR" 0 ((9719.70848 8103.31833) (9638.00905 8103.31176) (9619.15441 8099.55407) (9573.90554 8101.97251)
(9562.59333 8095.77670)))
("SF_SOLAR" 0 ((9585.21776 7948.71799) (9562.59333 7948.71799)))
("SF_SOLAR" 0 ((9562.59333 7948.71799) (9562.59333 7922.32274)))
("SF_SOLAR" 0 ((9566.36595 8186.27443) (9566.36595 8174.96222)))
("SF_SOLAR" 0 ((9570.13575 8050.52783) (9575.11041 8031.82885) (9581.45486 8028.05814) (9739.81900 8027.90339)))
("SF_SOLAR" 0 ((9585.21776 8133.48416) (9585.21776 8118.40113)))
("SF_SOLAR" 0 ((9585.21776 7993.96674) (9743.58880 7993.96674)))
("SF_SOLAR" 0 ((9585.21776 7993.96674) (9586.26867 7978.88394) (9596.52998 7948.71799)))
("SF_MASONRY_AND_ARCH" 0 ((9592.76018 5539.21527) (9592.76018 5512.82093)))
("SF_MASONRY_AND_ARCH" 0 ((9883.10803 5248.86878) (9868.02319 5245.10452) (9611.61482 5244.94977) (9592.76018
5233.78541)))
("SF_MASONRY_AND_ARCH" 0 ((9713.42477 2775.26369) (9592.76018 2771.49321)))
("SF_MASONRY_AND_ARCH" 0 ((9754.90102 1987.17975) (9739.81900 1990.95023) (9660.63348 1990.80249) (9645.55147
1987.18665) (9611.61482 1990.94400) (9592.76018 1987.17975)))
("SF_MASONRY_AND_ARCH" 0 ((9792.61029 795.62500) (9770.13292 787.02828) (9758.66606 776.92647) (9641.77885 780.54299)
(9592.76018 776.77319)))
("SF_MASONRY_AND_ARCH" 0 ((9592.76018 422.32183) (9856.71097 426.09446)))
("SF_SOLAR" 0 ((9596.52998 7948.71799) (9781.29808 7948.71799)))
("SF_SOLAR" 0 ((9596.52998 7948.71799) (9596.52998 7922.32274)))
("SF_MASONRY_AND_ARCH" 0 ((10007.54242 6398.94423) (9996.23020 6398.94423) (9868.02319 6398.94423) (9849.17138
6398.94423) (9649.32127 6395.01889) (9634.23925 6387.93462) (9596.52998 6391.40271)))
("SF_MASONRY_AND_ARCH" 0 ((9596.52998 6202.86584) (9638.00905 6206.63643)))
("SF_MASONRY_AND_ARCH" 0 ((9596.52998 6108.59729) (9626.69683 6108.44921) (9640.57545 6100.90781) (9638.00905
6063.34842)))
("SF_MASONRY_AND_ARCH" 0 ((9596.52998 6067.11923) (9604.07930 6063.49649) (9638.00905 6063.34842)))
("SF_MASONRY_AND_ARCH" 0 ((9596.52998 5953.99706) (9615.38462 5957.76109) (9671.94570 5955.04695) (9720.96437
5957.76765)))
("SF_MASONRY_AND_ARCH" 0 ((9596.52998 5795.62602) (9604.07240 5791.85520)))
("SF_MASONRY_AND_ARCH" 0 ((9596.52998 5109.35102) (9638.00905 5116.89333)))
("SF_MASONRY_AND_ARCH" 0 ((9611.61482 4777.52681) (9600.30260 4777.52681) (9596.52998 4773.75566)))
("SF_MASONRY_AND_ARCH" 0 ((9645.55147 3985.67161) (9634.23925 3993.05803) (9596.52998 3993.21267)))
("SF_MASONRY_AND_ARCH" 0 ((9596.52998 3951.73495) (9596.52998 3959.27602)))
("SF_MASONRY_AND_ARCH" 0 ((9845.39876 3740.57274) (9815.23473 3744.34389) (9596.52998 3740.57274)))
("SF_MASONRY_AND_ARCH" 0 ((9630.46663 3555.80667) (9622.77862 3545.55090) (9596.52998 3536.95351)))
("SF_MASONRY_AND_ARCH" 0 ((9596.52998 3469.08020) (9732.27658 3469.08643) (9773.75566 3472.84446) (9788.83767
3469.22794) (9889.81290 3466.57319) (9950.98133 3472.84446) (10079.18552 3469.08020) (10105.57975 3472.85068)))
("SF_MASONRY_AND_ARCH" 0 ((9596.52998 3099.54751) (9604.07930 3093.20995) (9653.09106 3099.54129) (9841.62896
3095.77704) (9860.48360 3099.54751)))
("SF_MASONRY_AND_ARCH" 0 ((9596.52998 2522.62443) (9622.92704 2522.62443)))
("SF_MASONRY_AND_ARCH" 0 ((9607.84219 2454.75113) (9596.52998 2454.75113)))
("SF_MASONRY_AND_ARCH" 0 ((9596.52998 1263.19853) (9622.91946 1261.99367) (9634.38631 1244.49853) (9641.77885
1240.57410)))
("SF_MASONRY_AND_ARCH" 0 ((9785.06787 350.67873) (9758.67364 358.21425) (9656.86369 354.30147) (9641.77885 350.68563)
(9596.52998 354.44853)))
("SF_MASONRY_AND_ARCH" 0 ((9638.00905 177.22568) (9604.07930 177.37274) (9596.52998 180.99548)))
("SF_MASONRY_AND_ARCH" 0 ((9679.48812 5335.59536) (9607.84977 5331.67704) (9600.30260 5328.05430)))
("SF_MASONRY_AND_ARCH" 0 ((9600.30260 5003.77115) (9615.38462 5007.54106) (9645.54389 5007.39321) (9653.09106
5003.77115)))
("SF_MASONRY_AND_ARCH" 0 ((9619.15441 4728.50679) (9600.30260 4724.73563)))
("SF_MASONRY_AND_ARCH" 0 ((9626.69683 4596.53133) (9611.61482 4600.28812) (9600.30260 4596.53133)))
("SF_MASONRY_AND_ARCH" 0 ((9600.30260 4102.56369) (9604.07240 4095.02262)))
("SF_MASONRY_AND_ARCH" 0 ((9600.30260 4087.48156) (9604.07240 4095.02262)))
("SF_MASONRY_AND_ARCH" 0 ((9600.30260 4068.62749) (9607.84977 4068.62749) (9622.92704 4068.62749) (9717.19457
4068.62749)))
("SF_MASONRY_AND_ARCH" 0 ((9600.30260 3684.01165) (9611.61482 3687.76968) (9630.46663 3684.01165)))
("SF_MASONRY_AND_ARCH" 0 ((9630.46663 3597.28507) (9607.84977 3597.43281) (9600.30260 3601.05554)))
("SF_MASONRY_AND_ARCH" 0 ((9600.30260 3190.04525) (9619.15441 3191.71686) (9645.55147 3186.27455) (9702.11256
3186.27455) (9736.04921 3186.27455) (9830.31674 3186.27455) (9856.71097 3186.27455)))
("SF_MASONRY_AND_ARCH" 0 ((9739.81900 2941.17647) (9732.27172 2944.79231) (9713.42477 2941.18959) (9690.80034
2944.94695) (9668.17590 2941.33111) (9611.61482 2944.79921) (9600.30260 2941.17647)))
("SF_MASONRY_AND_ARCH" 0 ((9626.69683 2741.32704) (9625.49197 2726.24434) (9607.84977 2711.46403) (9600.30260
2714.93213)))
("SF_MASONRY_AND_ARCH" 0 ((9841.62896 2405.73179) (9834.08167 2402.25679) (9807.69231 2405.58326) (9792.61029
2399.39423) (9769.98586 2405.72557) (9679.48812 2403.15848) (9615.38462 2409.49536) (9600.30260 2405.73179)))
("SF_MASONRY_AND_ARCH" 0 ((9600.30260 2311.46278) (9607.84977 2315.08631) (9668.17590 2315.23405)))
("SF_MASONRY_AND_ARCH" 0 ((9683.25792 2239.81900) (9645.55147 2236.06165) (9607.84977 2239.67127) (9600.30260
2236.04853)))
("SF_MASONRY_AND_ARCH" 0 ((9653.09106 1862.74536) (9600.30260 1855.20362)))
("SF_MASONRY_AND_ARCH" 0 ((9600.30260 1613.87726) (9611.61482 1617.64084) (9698.33993 1613.87726) (9717.19457
1617.64706)))
("SF_MASONRY_AND_ARCH" 0 ((9600.30260 1342.38405) (9626.69683 1338.90837) (9645.55147 1342.23563) (9660.63348
1338.61833) (9683.25792 1342.08710) (9694.57014 1338.61143)))
("SF_MASONRY_AND_ARCH" 0 ((9626.69683 1176.47059) (9611.61482 1180.08710) (9600.30260 1176.47059)))
("SF_MASONRY_AND_ARCH" 0 ((9671.94570 987.93269) (9649.32127 995.32738) (9607.84977 995.32738) (9600.30260 991.70532)))
("SF_MASONRY_AND_ARCH" 0 ((9679.48812 855.95871) (9607.84977 852.03903) (9600.30260 848.41629)))
("SF_MASONRY_AND_ARCH" 0 ((9645.55147 720.21210) (9619.15441 723.98190) (9600.30260 720.21210)))
("SF_MASONRY_AND_ARCH" 0 ((9600.30260 595.77771) (9607.84219 595.77771)))
("SF_MASONRY_AND_ARCH" 0 ((9762.44344 539.21663) (9747.36143 535.44400) (9713.42477 539.20283) (9694.57014 535.45090)
(9611.61482 535.45090) (9600.30260 539.21663)))
("SF_MASONRY_AND_ARCH" 0 ((9600.30260 245.09898) (9607.84219 248.86878)))
("SF_MASONRY_AND_ARCH" 0 ((9894.42025 86.72794) (9604.22704 85.52930) (9600.30260 79.18552)))
("SF_SOLAR" 0 ((9607.84219 8084.46448) (9604.07240 8069.38167)))
("SF_MASONRY_AND_ARCH" 0 ((9622.92704 5712.66968) (9604.07240 5712.66968)))
("SF_MASONRY_AND_ARCH" 0 ((9604.07240 5678.73303) (9622.92704 5682.50385)))
("SF_MASONRY_AND_ARCH" 0 ((9604.07240 5448.71753) (9653.09106 5448.56968) (9664.40328 5444.94762)))
("SF_MASONRY_AND_ARCH" 0 ((9638.00905 5135.74661) (9604.07240 5135.74661)))
("SF_MASONRY_AND_ARCH" 0 ((9800.14989 4894.41889) (9641.77885 4896.99242) (9611.61968 4890.94491) (9604.07240
4894.41889)))
("SF_MASONRY_AND_ARCH" 0 ((10113.12217 4513.57466) (10101.80995 4517.19740) (10015.08201 4517.35204) (9996.23020
4521.10950) (9966.06335 4515.68054) (9845.39876 4517.33891) (9826.54695 4513.58088) (9792.61029 4517.33891) (9751.13122
4517.19740) (9736.04921 4513.58778) (9717.19457 4517.33891) (9604.07240 4517.34581)))
("SF_MASONRY_AND_ARCH" 0 ((9796.38009 4423.07692) (9743.58880 4422.92229) (9724.73699 4411.91934) (9604.07240
4411.76471)))
("SF_MASONRY_AND_ARCH" 0 ((9604.07240 4321.26697) (9611.61968 4317.79231) (9660.63348 4325.03122) (9709.65215
4324.88971) (9720.95950 4321.56968) (9739.81900 4336.19536) (9845.39876 4336.49819) (9868.02319 4343.89140)))
("SF_MASONRY_AND_ARCH" 0 ((9868.02319 4193.06143) (9622.92704 4193.05520) (9604.07240 4189.29152)))
("SF_MASONRY_AND_ARCH" 0 ((9709.65215 4098.79378) (9698.33993 4102.41584) (9660.63348 4102.55747) (9604.07240
4095.02262)))
("SF_MASONRY_AND_ARCH" 0 ((9739.81900 3861.23722) (9717.19457 3857.46606) (9660.63348 3857.61414) (9634.23925
3865.00090) (9611.61968 3864.85928) (9604.07240 3861.23722)))
("SF_MASONRY_AND_ARCH" 0 ((9604.07240 3348.41629) (9683.25792 3344.64581)))
("SF_MASONRY_AND_ARCH" 0 ((9604.07240 3291.85520) (9607.99751 3281.75407) (9630.46663 3284.31346)))
("SF_MASONRY_AND_ARCH" 0 ((9604.07240 3035.44468) (9720.96437 3035.45090) (9743.58880 3039.21595) (9785.06787
3035.44468)))
("SF_MASONRY_AND_ARCH" 0 ((9634.23925 2631.97613) (9634.08394 2613.12217) (9630.31335 2605.59355) (9622.92704
2600.29310) (9604.07240 2601.80995)))
("SF_MASONRY_AND_ARCH" 0 ((9641.77885 2111.61414) (9634.23167 2107.99061) (9604.07240 2107.84287)))
("SF_MASONRY_AND_ARCH" 0 ((9777.52545 1742.08145) (9732.27658 1732.86821) (9604.07240 1734.53903)))
("SF_MASONRY_AND_ARCH" 0 ((9604.07240 1527.14932) (9698.33993 1527.15554) (9720.96437 1530.91912) (9766.21324
1530.77206) (9777.52545 1527.14932)))
("SF_MASONRY_AND_ARCH" 0 ((9604.07240 1429.10916) (9800.14989 1426.53733) (9841.62896 1436.50385) (9924.58428
1436.64536) (9958.52093 1432.88665) (9981.14536 1440.42138)))
("SF_MASONRY_AND_ARCH" 0 ((9604.07240 1101.05486) (9630.46663 1100.90781) (9653.09106 1096.22873) (9664.40328
1089.74265)))
("SF_SOLAR" 0 ((9607.84219 8118.40113) (9607.84219 8125.94276)))
("SF_SOLAR" 0 ((9607.84219 8035.44502) (9607.84219 8046.75724)))
("SF_SOLAR" 0 ((9611.61482 8016.59118) (9611.61482 8005.27896)))
("SF_MASONRY_AND_ARCH" 0 ((9619.15441 4785.06787) (9611.61482 4837.85781)))
("SF_MASONRY_AND_ARCH" 0 ((9611.61482 4777.52681) (9619.15441 4728.50679)))
("SF_MASONRY_AND_ARCH" 0 ((9619.15441 4785.06787) (9611.61482 4777.52681)))
("SF_MASONRY_AND_ARCH" 0 ((9611.61482 4291.10147) (9608.00452 4279.79548) (9615.39152 4272.40192) (9702.11256
4272.24072) (9724.73699 4268.47704) (9819.00452 4272.24695)))
("SF_MASONRY_AND_ARCH" 0 ((9615.38462 2635.74661) (9634.23925 2631.97613)))
("SF_SOLAR" 0 ((9622.92704 7963.80090) (9622.92704 7975.11312) (9619.15441 7978.88394)))
("SF_MASONRY_AND_ARCH" 0 ((9619.15441 5840.87489) (9634.23925 5840.87489)))
("SF_MASONRY_AND_ARCH" 0 ((9619.15441 4785.06787) (9762.44344 4783.39627) (9781.29808 4788.54253) (9792.61029
4785.21595) (9849.17138 4785.06787) (9871.79581 4788.68405) (9886.87783 4785.07410) (9905.73247 4787.64118) (9950.98133
4777.52681)))
("SF_MASONRY_AND_ARCH" 0 ((9619.15441 4728.50679) (9660.63348 4728.35871) (9671.94570 4724.73563)))
("SF_MASONRY_AND_ARCH" 0 ((9622.92704 5712.66968) (9622.92704 5682.50385)))
("SF_MASONRY_AND_ARCH" 0 ((9634.23925 5723.98190) (9622.92704 5712.66968)))
("SF_MASONRY_AND_ARCH" 0 ((9954.75113 5674.96222) (9924.58428 5678.72647) (9898.19005 5674.96222) (9732.27658
5674.96878) (9709.65215 5678.73303) (9687.02771 5675.11686) (9660.63348 5678.72647) (9641.77885 5674.97534) (9622.92704
5682.50385)))
("SF_MASONRY_AND_ARCH" 0 ((9622.92704 2564.10283) (9622.92704 2522.62443)))
("SF_MASONRY_AND_ARCH" 0 ((9653.09106 2518.85396) (9622.92704 2522.62443)))
("SF_SOLAR" 0 ((9626.69683 8005.27896) (9630.46663 8016.59118)))
("SF_MASONRY_AND_ARCH" 0 ((9626.69683 5791.85520) (9638.00905 5788.08439)))
("SF_MASONRY_AND_ARCH" 0 ((9626.69683 5607.08857) (9622.92704 5622.17195) (9626.69683 5641.02557)))
("SF_MASONRY_AND_ARCH" 0 ((9660.63348 5554.29864) (9630.62195 5555.50317) (9626.69683 5569.38201)))
("SF_MASONRY_AND_ARCH" 0 ((9626.69683 1176.47059) (9626.69683 1142.53394)))
("SF_MASONRY_AND_ARCH" 0 ((9626.69683 1176.47059) (9641.77885 1184.00543) (9894.42025 1184.01787) (9920.81448
1187.78281)))
("SF_MASONRY_AND_ARCH" 0 ((9638.00905 6338.61244) (9630.46663 6342.38303)))
("SF_MASONRY_AND_ARCH" 0 ((9630.46663 3684.01165) (9630.46663 3627.45057)))
("SF_MASONRY_AND_ARCH" 0 ((9732.27658 3691.55396) (9683.25792 3691.40554) (9630.46663 3684.01165)))
("SF_MASONRY_AND_ARCH" 0 ((9630.46663 3597.28507) (9739.81900 3597.27885) (9754.90102 3593.51459)))
("SF_MASONRY_AND_ARCH" 0 ((9630.46663 3597.28507) (9630.46663 3555.80667)))
("SF_MASONRY_AND_ARCH" 0 ((9702.11256 3555.80667) (9660.63348 3555.80667) (9653.09106 3555.80667) (9630.46663
3555.80667)))
("SF_MASONRY_AND_ARCH" 0 ((9630.46663 1674.20814) (9641.77885 1670.43835)))
("SF_MASONRY_AND_ARCH" 0 ((9634.23925 5516.59084) (9645.55147 5520.35577) (9728.50679 5520.35577) (9751.13122
5516.59774) (9803.40464 5521.56652) (9798.94649 5542.98643) (9785.06787 5558.06980)))
("SF_MASONRY_AND_ARCH" 0 ((9645.55147 3985.67161) (9644.49434 3970.58824) (9634.23925 3955.50486)))
("SF_MASONRY_AND_ARCH" 0 ((9845.39876 2631.97613) (9819.00452 2634.54864) (9762.44344 2629.40283) (9705.88235
2634.54864) (9671.94570 2632.13077) (9656.86369 2635.73348) (9634.23925 2631.97613)))
("SF_SOLAR" 0 ((9638.00905 8114.63054) (9641.48337 8122.17851) (9638.00905 8133.48416)))
("SF_SOLAR" 0 ((9641.77885 8069.38167) (9638.00905 8088.23529)))
("SF_MASONRY_AND_ARCH" 0 ((9638.00905 6244.34389) (9645.69853 6252.18145) (9751.13122 6252.03337) (9773.75566
6259.42692)))
("SF_MASONRY_AND_ARCH" 0 ((9638.00905 6206.63643) (9653.09106 6203.02059) (9675.71550 6206.48824) (9736.04921
6199.09502)))
("SF_MASONRY_AND_ARCH" 0 ((9641.77885 6221.71946) (9638.00905 6217.94864) (9638.00905 6206.63643)))
("SF_MASONRY_AND_ARCH" 0 ((9728.50679 6063.34842) (9638.00905 6063.34842)))
("SF_MASONRY_AND_ARCH" 0 ((9638.00905 5742.83552) (9638.00905 5788.08439)))
("SF_MASONRY_AND_ARCH" 0 ((9781.29808 5791.85520) (9736.04921 5794.42851) (9649.32127 5791.70713) (9638.00905
5788.08439)))
("SF_MASONRY_AND_ARCH" 0 ((9638.00905 5135.74661) (9638.00905 5116.89333)))
("SF_MASONRY_AND_ARCH" 0 ((9638.00905 5135.74661) (9664.40328 5135.89468) (9690.80034 5143.28145) (9777.52545
5143.13982) (9788.83767 5139.51776)))
("SF_MASONRY_AND_ARCH" 0 ((9781.29808 5109.35102) (9713.42477 5113.12217) (9671.94570 5109.49943) (9638.00905
5116.89333)))
("SF_MASONRY_AND_ARCH" 0 ((9638.00905 218.70192) (9638.00905 177.22568)))
("SF_MASONRY_AND_ARCH" 0 ((9638.00905 177.22568) (9807.69231 177.22568)))
("SF_MASONRY_AND_ARCH" 0 ((9773.75566 6297.13416) (9705.88235 6300.90498) (9645.55633 6297.28880) (9639.36233
6301.05962) (9641.77885 6312.21719)))
("SF_MASONRY_AND_ARCH" 0 ((9641.77885 2458.52161) (9653.09106 2462.29287)))
("SF_MASONRY_AND_ARCH" 0 ((9641.77885 309.19966) (9649.32127 309.19966)))
("SF_MASONRY_AND_ARCH" 0 ((9641.77885 248.86878) (9649.32127 260.18100)))
("SF_MASONRY_AND_ARCH" 0 ((9800.14989 4894.41889) (9802.56923 4935.74287) (9796.37319 4939.51380) (9728.50679
4939.81618) (9713.42477 4943.42579) (9698.33993 4939.81618) (9653.09864 4939.51991) (9645.55147 4935.89785)))
("SF_MASONRY_AND_ARCH" 0 ((9645.55147 3985.67161) (9656.86369 3989.44152)))
("SF_MASONRY_AND_ARCH" 0 ((9645.55147 3288.08473) (9747.36143 3288.07851) (9769.98586 3284.31346) (9792.61029
3288.07161) (9830.31674 3284.31346)))
("SF_MASONRY_AND_ARCH" 0 ((9649.32127 663.65102) (9645.55147 720.21210)))
("SF_MASONRY_AND_ARCH" 0 ((10388.38518 720.21210) (10369.53337 723.97500) (10301.66007 720.21210) (10256.41120
723.98190) (10211.16233 720.21697) (10105.57975 720.21697) (10060.33088 727.73925) (9966.06335 720.36538) (9947.20871
723.97568) (9924.58428 720.50758) (9909.50226 723.97568) (9668.17590 723.98190) (9645.55147 720.21210)))
("SF_MASONRY_AND_ARCH" 0 ((9739.81900 3910.25600) (9724.73699 3913.87907) (9649.32127 3914.02715)))
("SF_MASONRY_AND_ARCH" 0 ((9649.32127 580.69287) (9642.97749 584.61878) (9641.79265 592.00509) (9649.32127 629.71437)))
("SF_MASONRY_AND_ARCH" 0 ((9649.32127 271.49321) (9649.32127 260.18100)))
("SF_MASONRY_AND_ARCH" 0 ((9724.73699 260.18100) (9649.32127 260.18100)))
("SF_SOLAR" 0 ((9653.09106 8035.44502) (9653.09106 8042.98643)))
("SF_SOLAR" 0 ((9653.09106 8001.50837) (9653.09106 8016.59118)))
("SF_MASONRY_AND_ARCH" 0 ((9679.48812 6112.36810) (9664.40328 6115.98394) (9653.09106 6112.36810)))
("SF_MASONRY_AND_ARCH" 0 ((9653.09106 4977.37557) (9653.09106 5003.77115)))
("SF_MASONRY_AND_ARCH" 0 ((9653.09106 5003.77115) (9660.64038 5007.39321) (9781.59355 5009.96652) (9788.69061
5033.93665) (9788.83767 5064.10215)))
("SF_MASONRY_AND_ARCH" 0 ((9653.09106 2518.85396) (9653.09106 2462.29287)))
("SF_MASONRY_AND_ARCH" 0 ((10033.93665 2515.08269) (10011.31222 2522.61753) (9992.45758 2519.00860) (9962.29355
2522.62443) (9943.43891 2519.00170) (9883.10803 2518.85396) (9860.48360 2522.61821) (9679.48812 2522.61821) (9653.09106
2518.85396)))
("SF_MASONRY_AND_ARCH" 0 ((9879.33541 2458.52161) (9868.02319 2461.99661) (9852.94118 2458.52783) (9705.88235
2458.52161) (9653.09106 2462.29287)))
("SF_MASONRY_AND_ARCH" 0 ((9653.09106 1862.74536) (9653.09106 1885.36980)))
("SF_MASONRY_AND_ARCH" 0 ((9653.09106 1862.74536) (9664.40328 1859.12183) (9736.04921 1858.97410)))
("SF_MASONRY_AND_ARCH" 0 ((9653.09106 1040.72398) (9660.47885 1048.27127) (9664.40328 1089.74265)))
("SF_MASONRY_AND_ARCH" 0 ((9664.40328 1938.15962) (9660.63348 1941.93088) (9664.40328 1945.70136)))
("SF_MASONRY_AND_ARCH" 0 ((9698.33993 1244.34389) (9690.79276 1240.72115) (9664.40328 1240.57410)))
("SF_MASONRY_AND_ARCH" 0 ((9664.40328 1089.74265) (9683.25792 1085.97285)))
("SF_MASONRY_AND_ARCH" 0 ((9668.17590 4630.46799) (9675.71550 4622.92568) (9683.25792 4622.92568)))
("SF_MASONRY_AND_ARCH" 0 ((9702.11256 2111.61414) (9668.17590 2107.84287)))
("SF_MASONRY_AND_ARCH" 0 ((9671.94570 4709.65351) (9671.94570 4724.73563)))
("SF_MASONRY_AND_ARCH" 0 ((9671.94570 4724.73563) (9694.57014 4730.17839) (9736.04921 4728.51301) (9754.90102
4732.26482) (9811.46210 4724.88405) (9924.58428 4724.74253) (9939.66912 4728.21029) (9950.98133 4724.73563)))
("SF_MASONRY_AND_ARCH" 0 ((9671.94570 4690.79898) (9675.71550 4668.17455)))
("SF_MASONRY_AND_ARCH" 0 ((9671.94570 987.93269) (9671.94570 961.53846)))
("SF_MASONRY_AND_ARCH" 0 ((9671.94570 987.93269) (9687.02771 991.70441) (9796.38009 991.70441)))
("SF_SOLAR" 0 ((9675.71550 8174.96222) (9675.71550 8182.50385)))
("SF_SOLAR" 0 ((9675.71550 8133.48416) (9675.71550 8118.40113)))
("SF_SOLAR" 0 ((9675.71550 8069.38167) (9675.71550 8084.46448)))
("SF_SOLAR" 0 ((9675.71550 8050.52783) (9675.71550 8039.21561)))
("SF_SOLAR" 0 ((9675.71550 8005.27896) (9675.71550 8016.59118)))
("SF_MASONRY_AND_ARCH" 0 ((9675.71550 5554.29864) (9687.02771 5558.06290) (9732.27172 5554.44672) (9739.81900
5558.06980)))
("SF_MASONRY_AND_ARCH" 0 ((9675.71550 3989.44152) (9736.04921 3993.20645) (9754.90102 3989.44842) (9871.79581
3989.29367) (9886.87783 3985.67161)))
("SF_MASONRY_AND_ARCH" 0 ((9675.71550 2601.80995) (9717.19457 2601.80995)))
("SF_MASONRY_AND_ARCH" 0 ((9675.71550 1674.20814) (9732.27658 1674.35588) (9743.58880 1677.97794)))
("SF_MASONRY_AND_ARCH" 0 ((9679.48812 5837.10407) (9739.81900 5836.95600) (9754.90102 5833.33982) (9773.75566
5836.80792) (9785.06787 5833.33326)))
("SF_MASONRY_AND_ARCH" 0 ((9679.48812 916.28959) (9705.88235 912.51980) (9788.83767 916.13495) (9796.22545 912.36448)
(9800.14989 901.20758)))
("SF_MASONRY_AND_ARCH" 0 ((9683.25792 2239.81900) (9758.67364 2232.43190) (9811.46210 2239.81900)))
("SF_MASONRY_AND_ARCH" 0 ((9683.25792 2239.81900) (9684.45588 2258.66606) (9690.80034 2266.21391)))
("SF_MASONRY_AND_ARCH" 0 ((9687.02771 1934.38914) (9698.33993 1938.15962)))
("SF_MASONRY_AND_ARCH" 0 ((9690.80034 6112.36810) (9717.19457 6115.98394) (9736.04921 6101.05588)))
("SF_MASONRY_AND_ARCH" 0 ((9694.57014 5444.94762) (9709.65215 5441.32455) (9781.29808 5441.02839) (9792.61029
5437.40532)))
("SF_SOLAR" 0 ((9698.33993 8118.40113) (9698.33993 8133.48416)))
("SF_SOLAR" 0 ((9698.33993 8088.23529) (9698.33993 8069.38167)))
("SF_SOLAR" 0 ((9698.33993 8035.44502) (9698.33993 8046.75724)))
("SF_MASONRY_AND_ARCH" 0 ((9860.48360 4611.61346) (9856.55769 4622.77172) (9849.17138 4626.54219) (9698.33993
4622.92568)))
("SF_MASONRY_AND_ARCH" 0 ((9698.33993 1244.34389) (9713.42477 1240.57410)))
("SF_MASONRY_AND_ARCH" 0 ((9698.33993 1244.34389) (9702.26584 1258.21561) (9717.19457 1255.65611)))
("SF_MASONRY_AND_ARCH" 0 ((9705.88235 5346.90758) (9705.88235 5335.59536)))
("SF_MASONRY_AND_ARCH" 0 ((9792.61029 5437.40532) (9796.08394 5407.23982) (9785.06165 5389.59038) (9739.81900
5388.53439) (9709.65215 5395.92760)))
("SF_MASONRY_AND_ARCH" 0 ((9883.10803 2835.59604) (9724.73699 2835.58982) (9709.65215 2831.82477)))
("SF_MASONRY_AND_ARCH" 0 ((9713.42477 2775.26369) (9732.27658 2771.49943) (9758.67364 2775.10905) (9769.98586
2771.64095) (9837.85916 2771.49321)))
("SF_MASONRY_AND_ARCH" 0 ((9713.42477 2775.26369) (9717.19457 2801.65939)))
("SF_MASONRY_AND_ARCH" 0 ((9732.27658 1236.80147) (9713.42477 1240.57410)))
("SF_MASONRY_AND_ARCH" 0 ((9717.19457 1255.65611) (9713.42477 1240.57410)))
("SF_SOLAR" 0 ((9717.19457 7963.80090) (9717.19457 7975.11312)))
("SF_MASONRY_AND_ARCH" 0 ((9717.19457 5976.62149) (9720.96437 5957.76765)))
("SF_MASONRY_AND_ARCH" 0 ((9717.19457 2911.01029) (9720.95814 2895.92760) (9717.19457 2880.84491)))
("SF_MASONRY_AND_ARCH" 0 ((9728.50679 1610.10464) (9717.19457 1617.64706)))
("SF_MASONRY_AND_ARCH" 0 ((9720.96437 1628.95928) (9717.19457 1617.64706)))
("SF_MASONRY_AND_ARCH" 0 ((9732.27658 1263.19853) (9724.73699 1263.19853) (9717.19457 1255.65611)))
("SF_SOLAR" 0 ((9720.96437 7877.07387) (9736.04921 7877.07387) (9743.58880 7877.07387) (9751.13122 7880.84468)))
("SF_ARCHITECTURE" 0 ((9720.96437 6828.80848) (9739.81900 6828.80848) (10098.04016 6828.80848) (10109.35238
6828.80848)))
("SF_ARCHITECTURE" 0 ((9724.73699 7571.64400) (9720.97127 7560.33179) (9720.96437 6828.80848)))
("SF_MASONRY_AND_ARCH" 0 ((10037.70645 5953.99706) (9917.04468 5950.38088) (9830.31674 5957.61946) (9743.58880
5953.99706) (9720.96437 5957.76765)))
("SF_MASONRY_AND_ARCH" 0 ((9720.96437 855.95871) (9751.13122 848.41629)))
("SF_SOLAR" 0 ((9747.36143 8137.25498) (9724.73699 8141.02557)))
("SF_SOLAR" 0 ((9728.50679 8174.96222) (9721.11968 8163.65000) (9724.73699 8141.02557)))
("SF_ARCHITECTURE" 0 ((9724.73699 7571.64400) (9720.96437 7586.72704) (9724.73699 7635.74661)))
("SF_ARCHITECTURE" 0 ((9724.73699 7571.64400) (9739.81900 7575.41482) (9811.46210 7571.79208) (9856.71097 7586.72048)
(9886.87783 7582.95622) (10056.56109 7582.96278) (10090.49774 7586.72048) (10113.12217 7579.18552)))
("SF_MASONRY_AND_ARCH" 0 ((9743.58880 3352.18676) (9743.22081 3338.30826) (9724.73699 3337.10407)))
("SF_SOLAR" 0 ((9728.50679 8174.96222) (9751.13122 8171.19163)))
("SF_SOLAR" 0 ((9732.27658 8193.81606) (9728.50679 8174.96222)))
("SF_MASONRY_AND_ARCH" 0 ((9852.94118 6044.49480) (9830.31674 6055.65894) (9739.36810 6055.51086) (9728.50679
6063.34842)))
("SF_MASONRY_AND_ARCH" 0 ((9736.04921 6101.05588) (9728.50679 6063.34842)))
("SF_MASONRY_AND_ARCH" 0 ((9796.38009 2269.98518) (9728.50679 2266.21391)))
("SF_MASONRY_AND_ARCH" 0 ((9728.50679 1338.61143) (9769.98586 1342.38405)))
("SF_MASONRY_AND_ARCH" 0 ((9969.83314 6018.09955) (9950.98133 6014.47681) (9868.02319 6014.18054) (9849.17138
6007.98529) (9837.85916 6010.26233) (9822.77432 6006.79389) (9739.82590 6006.93541) (9732.27658 6010.55814)))
("SF_MASONRY_AND_ARCH" 0 ((9732.27658 4472.09695) (9747.36143 4468.32579)))
("SF_SOLAR" 0 ((9736.04921 8054.29864) (9739.81900 8027.90339)))
("SF_MASONRY_AND_ARCH" 0 ((9743.58880 6101.05588) (9736.04921 6101.05588)))
("SF_MASONRY_AND_ARCH" 0 ((9736.04921 4068.62749) (9747.21301 4068.62749) (9754.90102 4076.16934)))
("SF_SOLAR" 0 ((9739.81900 8099.54751) (9751.13122 8103.31833)))
("SF_SOLAR" 0 ((9743.58880 7993.96674) (9739.81900 8027.90339)))
("SF_MASONRY_AND_ARCH" 0 ((9739.81900 3861.23722) (9743.58258 3895.17387) (9739.81900 3910.25600)))
("SF_MASONRY_AND_ARCH" 0 ((9890.64762 3925.33937) (9868.02319 3921.57511) (9754.90102 3921.41425) (9739.81900
3910.25600)))
("SF_MASONRY_AND_ARCH" 0 ((9890.64762 3853.69536) (9841.62896 3853.69536) (9785.06787 3853.69536) (9739.81900
3861.23722)))
("SF_SOLAR" 0 ((9751.13122 7956.25939) (9743.58880 7993.96674)))
("SF_MASONRY_AND_ARCH" 0 ((9743.58880 1700.60238) (9743.58880 1677.97794)))
("SF_MASONRY_AND_ARCH" 0 ((10128.20419 1681.75057) (10082.95532 1675.40611) (9743.58880 1677.97794)))
("SF_MASONRY_AND_ARCH" 0 ((9754.90102 1380.09050) (9743.58880 1380.09050)))
("SF_SOLAR" 0 ((9751.13122 8061.84005) (9747.36143 8069.38167)))
("SF_MASONRY_AND_ARCH" 0 ((9754.90102 4091.25147) (9747.36143 4098.79378)))
("SF_MASONRY_AND_ARCH" 0 ((9860.48360 2115.38462) (9845.39876 2111.62036) (9754.90860 2111.46640) (9747.36143
2107.84287)))
("SF_SOLAR" 0 ((9751.13122 8171.19163) (9758.37670 8148.56719) (9756.10588 8137.25498) (9766.06618 8110.85973)
(9769.98586 8058.06946)))
("SF_SOLAR" 0 ((9754.90102 8182.50385) (9751.13122 8171.19163)))
("SF_MASONRY_AND_ARCH" 0 ((9754.90102 3559.57794) (9751.13122 3552.03620)))
("SF_MASONRY_AND_ARCH" 0 ((9751.13122 1934.38914) (9748.55860 1941.93710) (9754.90102 1987.17975)))
("SF_SOLAR" 0 ((9777.52545 7993.96674) (9754.90102 7993.96674)))
("SF_MASONRY_AND_ARCH" 0 ((9754.90102 4091.25147) (9754.90102 4076.16934)))
("SF_MASONRY_AND_ARCH" 0 ((9754.90102 4091.25147) (9773.75566 4098.64536) (9811.46210 4102.41584) (9849.17138
4102.41584) (9860.48360 4098.79378)))
("SF_MASONRY_AND_ARCH" 0 ((9754.90102 4076.16934) (9762.44344 4068.62749)))
("SF_MASONRY_AND_ARCH" 0 ((9754.90102 3559.57794) (9754.90102 3593.51459)))
("SF_MASONRY_AND_ARCH" 0 ((9984.91799 3597.28507) (9943.43891 3600.75939) (9928.35690 3597.29129) (9766.21324
3597.13733) (9754.90102 3593.51459)))
("SF_MASONRY_AND_ARCH" 0 ((9754.90102 3559.57794) (9852.94118 3559.57794)))
("SF_MASONRY_AND_ARCH" 0 ((9935.89649 1987.17975) (9898.19005 1987.32749) (9886.87783 1990.79559) (9860.48360
1987.32749) (9841.62896 1990.95023) (9769.98586 1990.80249) (9754.90102 1987.17975)))
("SF_SOLAR" 0 ((9762.44344 7941.17647) (9766.21324 7922.32274)))
("SF_MASONRY_AND_ARCH" 0 ((9875.56561 6199.09502) (9762.44344 6199.09502)))
("SF_SOLAR" 0 ((9766.21324 8163.65000) (9924.58428 8163.65000)))
("SF_SOLAR" 0 ((9766.21324 8144.79638) (9871.79581 8144.78982) (9898.19005 8141.02557) (9924.58428 8144.79638)))
("SF_SOLAR" 0 ((9773.75566 8027.90339) (9766.21324 8027.90339)))
("SF_MASONRY_AND_ARCH" 0 ((9883.10803 5248.86878) (9883.25509 5282.80543) (9890.49434 5305.42986) (9886.72319
5315.68541) (9871.79581 5320.50633) (9807.69853 5316.89672) (9788.83281 5338.30984) (9766.21324 5343.13767)))
("SF_MASONRY_AND_ARCH" 0 ((9766.21324 2895.92760) (9777.52545 2892.16335) (9822.77432 2895.92760) (9875.56561
2892.15713)))
("SF_MASONRY_AND_ARCH" 0 ((9777.52545 260.18100) (9766.21324 263.95079)))
("SF_SOLAR" 0 ((9935.89649 8058.06946) (9769.98586 8058.06946)))
("SF_SOLAR" 0 ((9773.75566 8027.90339) (9769.98586 8058.06946)))
("SF_MASONRY_AND_ARCH" 0 ((9781.29808 5791.85520) (9784.01154 5765.45995) (9777.38462 5754.30238) (9769.98586
5750.37715)))
("SF_MASONRY_AND_ARCH" 0 ((9769.98586 1613.87726) (9777.53303 1606.48948) (9815.23473 1606.18710) (9826.54695
1602.56505)))
("SF_SOLAR" 0 ((9773.75566 8027.90339) (9871.79581 8027.89683) (9898.19005 8024.13281) (9935.89649 8027.90339)))
("SF_SOLAR" 0 ((9777.52545 7993.96674) (9777.52545 8020.36199) (9773.75566 8027.90339)))
("SF_MASONRY_AND_ARCH" 0 ((9773.75566 6259.42692) (9773.75566 6297.13416)))
("SF_MASONRY_AND_ARCH" 0 ((9966.06335 6300.90498) (9841.62896 6300.89842) (9826.54695 6297.28880) (9796.38009
6300.89842) (9773.75566 6297.13416)))
("SF_MASONRY_AND_ARCH" 0 ((9773.75566 6259.42692) (9788.83767 6255.66267) (9943.43891 6255.65611)))
("SF_SOLAR" 0 ((9777.52545 8099.54751) (9788.83767 8103.31176) (9856.71097 8099.69548) (9868.02319 8103.17025)
(9920.80758 8103.46629) (9928.35690 8107.08891)))
("SF_SOLAR" 0 ((9777.52545 7993.96674) (9785.06787 7993.96674) (9939.66912 7993.96674)))
("SF_SOLAR" 0 ((9777.52545 7993.96674) (9782.35373 7967.57172) (9789.89480 7952.64333) (9796.38631 7948.87262)
(9947.20871 7948.71799)))
("SF_MASONRY_AND_ARCH" 0 ((9777.52545 3695.32387) (9785.06787 3695.32387)))
("SF_MASONRY_AND_ARCH" 0 ((9777.52545 1742.08145) (9785.06787 1738.31165)))
("SF_MASONRY_AND_ARCH" 0 ((9777.52545 1742.08145) (9777.68077 1791.09525) (9785.06787 1798.64253)))
("SF_MASONRY_AND_ARCH" 0 ((9807.69231 1236.80147) (9777.52545 1233.03167)))
("SF_MASONRY_AND_ARCH" 0 ((9777.52545 260.18100) (9819.00452 252.64548) (9894.42025 252.78699) (9905.73247 256.11425)
(9917.04468 252.93552) (9939.66912 256.41120)))
("SF_MASONRY_AND_ARCH" 0 ((9777.52545 260.18100) (9784.92014 294.11765) (9785.06787 350.67873)))
("SF_MASONRY_AND_ARCH" 0 ((9781.29808 6104.82647) (9796.38009 6104.82647)))
("SF_MASONRY_AND_ARCH" 0 ((9781.29808 5791.85520) (9785.06787 5833.33326)))
("SF_MASONRY_AND_ARCH" 0 ((9864.25339 5090.49774) (9852.94118 5094.12048) (9796.38631 5094.42285) (9781.29808
5109.35102)))
("SF_MASONRY_AND_ARCH" 0 ((9788.83767 5139.51776) (9781.29808 5109.35102)))
("SF_MASONRY_AND_ARCH" 0 ((9913.27206 1338.61143) (9898.19005 1342.23563) (9815.23473 1342.53111) (9803.92251
1345.85769) (9781.29808 1342.38405)))
("SF_MASONRY_AND_ARCH" 0 ((9785.06787 5833.33326) (9830.31674 5829.56267) (9871.78824 5829.71086) (9879.33541
5833.33326)))
("SF_MASONRY_AND_ARCH" 0 ((9785.06787 3695.32387) (9785.06787 3706.63609)))
("SF_MASONRY_AND_ARCH" 0 ((9841.62896 3691.55396) (9830.31674 3695.17602) (9785.06787 3695.32387)))
("SF_MASONRY_AND_ARCH" 0 ((9788.83767 2948.71821) (9788.69061 3024.13247) (9785.06787 3035.44468)))
("SF_MASONRY_AND_ARCH" 0 ((9815.23473 3046.75690) (9785.06787 3035.44468)))
("SF_MASONRY_AND_ARCH" 0 ((9785.06787 1855.20362) (9778.72410 1847.65566) (9777.67387 1817.49717) (9785.06787
1798.64253)))
("SF_MASONRY_AND_ARCH" 0 ((9785.06787 1798.64253) (9868.02319 1802.25905) (9878.13201 1794.86516) (9879.33541
1776.01810)))
("SF_MASONRY_AND_ARCH" 0 ((9852.94118 358.22115) (9837.85916 354.59695) (9792.61516 354.30147) (9785.06787 350.67873)))
("SF_SOLAR" 0 ((9788.83767 8133.48416) (9792.61029 8122.17195)))
("SF_MASONRY_AND_ARCH" 0 ((9788.83767 5139.51776) (9811.46210 5135.89468) (9890.64762 5135.59853) (9905.73247
5131.98235) (9969.83314 5135.59197) (10000.00000 5120.67636) (10018.85464 5124.42817) (10120.66459 5124.42817)
(10135.74661 5120.95973) (10150.82862 5124.42817) (10301.66007 5124.42817) (10316.74208 5120.95973) (10354.44853
5124.43439)))
("SF_SOLAR" 0 ((9800.14989 7922.32274) (9798.95271 7933.62839) (9792.61029 7941.17647)))
("SF_MASONRY_AND_ARCH" 0 ((9898.19005 5441.17647) (9883.10803 5437.70181) (9868.02319 5441.16335) (9852.94118
5437.55373) (9792.61029 5437.40532)))
("SF_MASONRY_AND_ARCH" 0 ((9792.61029 2326.54627) (9792.61029 2345.39943)))
("SF_MASONRY_AND_ARCH" 0 ((9865.51075 531.67421) (9852.94321 539.06131) (9792.61029 535.44400)))
("SF_MASONRY_AND_ARCH" 0 ((9803.92251 4479.63801) (9796.38009 4472.09695)))
("SF_MASONRY_AND_ARCH" 0 ((9796.38009 4423.07692) (9815.23473 4411.76471)))
("SF_MASONRY_AND_ARCH" 0 ((9796.38009 4423.07692) (9800.14989 4434.38914)))
("SF_MASONRY_AND_ARCH" 0 ((9796.38009 4068.62749) (9811.46210 4068.62749)))
("SF_MASONRY_AND_ARCH" 0 ((9796.38009 3423.83133) (9803.92251 3416.28959)))
("SF_MASONRY_AND_ARCH" 0 ((9796.38009 2269.98518) (9796.38009 2303.92183)))
("SF_MASONRY_AND_ARCH" 0 ((9811.46210 2269.98518) (9796.38009 2269.98518)))
("SF_MASONRY_AND_ARCH" 0 ((9890.64762 991.70441) (9879.33541 991.70441) (9837.85916 991.70441) (9830.31674 991.70441)
(9796.38009 991.70441)))
("SF_MASONRY_AND_ARCH" 0 ((9803.92251 946.45645) (9796.52783 969.08088) (9796.38009 991.70441)))
("SF_MASONRY_AND_ARCH" 0 ((9807.69231 4973.60441) (9800.14989 4992.45894)))
("SF_MASONRY_AND_ARCH" 0 ((9800.14989 4894.41889) (9901.95984 4894.41267) (9913.27206 4890.64898)))
("SF_MASONRY_AND_ARCH" 0 ((9800.14989 3393.66516) (9796.39253 3340.87455) (9807.69231 3327.00294) (9819.00452
3329.56233)))
("SF_MASONRY_AND_ARCH" 0 ((9800.14989 3393.66516) (9803.92251 3416.28959)))
("SF_MASONRY_AND_ARCH" 0 ((9800.14989 3393.66516) (9818.99762 3394.86934) (9825.34208 3401.21312) (9826.54695
3412.51912)))
("SF_MASONRY_AND_ARCH" 0 ((9890.64762 1930.61867) (9868.02319 1934.38914) (9807.69921 1934.24140) (9800.14989
1930.61867)))
("SF_MASONRY_AND_ARCH" 0 ((9800.14989 1025.64197) (9822.77432 1040.57557) (9879.33054 1041.92885) (9885.67296
1048.27127) (9890.49434 1067.11821) (9887.17398 1082.20305) (9890.64762 1093.51527)))
("SF_MASONRY_AND_ARCH" 0 ((9800.14989 848.41629) (9815.23473 848.41629)))
("SF_SOLAR" 0 ((9803.92251 8069.38167) (9803.92251 8084.46448)))
("SF_SOLAR" 0 ((9803.92251 8035.44502) (9803.92251 8046.75724)))
("SF_SOLAR" 0 ((9803.92251 8005.27896) (9803.92251 8016.59118)))
("SF_MASONRY_AND_ARCH" 0 ((9803.92251 3416.28959) (9826.54695 3412.51912)))
("SF_MASONRY_AND_ARCH" 0 ((9856.71097 803.16742) (9845.39876 799.54468) (9803.92251 799.39762)))
("SF_MASONRY_AND_ARCH" 0 ((9807.69231 6108.59729) (9826.54695 6108.59729)))
("SF_MASONRY_AND_ARCH" 0 ((9811.46210 188.53790) (9807.69231 177.22568)))
("SF_MASONRY_AND_ARCH" 0 ((9807.69231 177.22568) (9841.62896 180.84084) (9860.48360 177.23054) (9947.20871 177.22568)))
("SF_SOLAR" 0 ((9811.46210 8137.25498) (9811.46210 8118.40113)))
("SF_SOLAR" 0 ((9811.46210 7982.65452) (9815.23473 7960.03020)))
("SF_MASONRY_AND_ARCH" 0 ((9811.46210 2269.98518) (9811.46210 2239.81900)))
("SF_MASONRY_AND_ARCH" 0 ((9901.95984 2269.98518) (9875.56561 2273.74876) (9811.46210 2269.98518)))
("SF_MASONRY_AND_ARCH" 0 ((9811.46210 2239.81900) (9826.54695 2236.04853)))
("SF_MASONRY_AND_ARCH" 0 ((9822.77432 1855.20362) (9834.08654 1855.20362)))
("SF_MASONRY_AND_ARCH" 0 ((9830.31674 1523.37952) (9822.77432 1527.14932)))
("SF_MASONRY_AND_ARCH" 0 ((9822.77432 1481.90045) (9822.77432 1474.35803)))
("SF_MASONRY_AND_ARCH" 0 ((9826.54695 3412.51912) (9905.73247 3408.74785)))
("SF_MASONRY_AND_ARCH" 0 ((9830.31674 3046.75690) (9852.94118 3054.29864)))
("SF_SOLAR" 0 ((9834.08654 8122.17195) (9834.08654 8137.25498)))
("SF_SOLAR" 0 ((9837.85916 8080.69389) (9834.08654 8069.38167)))
("SF_SOLAR" 0 ((9834.08654 8035.44502) (9834.08654 8046.75724)))
("SF_SOLAR" 0 ((9834.08654 8005.27896) (9834.08654 8016.59118)))
("SF_SOLAR" 0 ((9834.08654 7971.34231) (9834.08654 7986.42534)))
("SF_SOLAR" 0 ((9879.33541 7971.34231) (9834.08654 7971.34231)))
("SF_SOLAR" 0 ((9834.08654 7971.34231) (9834.08654 7960.03020)))
("SF_SOLAR" 0 ((9834.08654 7926.09355) (9834.08654 7941.17647)))
("SF_ARCHITECTURE" 0 ((9834.08654 6885.36980) (9834.09344 7055.05305) (9837.85226 7073.90622) (9837.85916 7515.08292)))
("SF_MASONRY_AND_ARCH" 0 ((9834.08654 3325.79186) (9905.73247 3325.93959) (9924.58428 3329.56233) (9992.45758
3325.79186)))
("SF_MASONRY_AND_ARCH" 0 ((9905.73247 6116.13869) (9894.42025 6116.13869) (9886.87783 6116.13869) (9837.85916
6112.36810)))
("SF_MASONRY_AND_ARCH" 0 ((9837.85916 4411.76471) (9868.02319 4407.99355)))
("SF_MASONRY_AND_ARCH" 0 ((9841.62896 2944.94695) (9924.58428 2944.94695)))
("SF_MASONRY_AND_ARCH" 0 ((9841.62896 2232.27726) (9879.33541 2236.04163) (9898.19005 2232.27726)))
("SF_MASONRY_AND_ARCH" 0 ((9841.62896 1236.80147) (9849.17138 1240.57410)))
("SF_MASONRY_AND_ARCH" 0 ((9860.48360 4272.24695) (9849.17138 4264.70588)))
("SF_MASONRY_AND_ARCH" 0 ((9852.94118 1251.88631) (9849.17138 1240.57410)))
("SF_MASONRY_AND_ARCH" 0 ((9901.95984 1244.34389) (9890.64762 1240.72115) (9849.17138 1240.57410)))
("SF_MASONRY_AND_ARCH" 0 ((10237.55656 482.65554) (10211.16233 478.88982) (10101.80995 478.73586) (10086.72794
475.11934) (9924.58428 475.10690) (9901.95984 471.34333) (9871.79581 474.81697) (9856.71855 471.50419) (9848.42364
478.89050) (9849.17138 490.19514)))
("SF_MASONRY_AND_ARCH" 0 ((9875.56561 5908.74819) (9852.94118 5908.74819)))
("SF_MASONRY_AND_ARCH" 0 ((9864.25339 4660.63348) (9855.19480 4668.18145) (9852.94118 4690.79898)))
("SF_MASONRY_AND_ARCH" 0 ((9909.50226 844.64649) (9901.95498 848.26855) (9852.94118 848.41629)))
("SF_MASONRY_AND_ARCH" 0 ((9852.94118 384.61538) (9852.94118 358.22115)))
("SF_MASONRY_AND_ARCH" 0 ((9852.94118 358.22115) (9954.75113 358.21425) (9973.60577 354.60385) (9988.68778 358.21425)
(10086.72036 358.36821) (10094.26753 361.99095)))
("SF_SOLAR" 0 ((9856.71097 8042.98643) (9856.71097 8035.44502)))
("SF_SOLAR" 0 ((9856.71097 8016.59118) (9856.71097 8005.27896)))
("SF_ARCHITECTURE" 0 ((9856.71097 7635.74661) (10079.18552 7635.74005) (10094.26753 7631.97590)))
("SF_MASONRY_AND_ARCH" 0 ((9947.20871 3288.08473) (9856.71097 3288.08473)))
("SF_MASONRY_AND_ARCH" 0 ((9856.71097 3186.27455) (9917.04468 3186.27455) (9928.35690 3193.81572)))
("SF_MASONRY_AND_ARCH" 0 ((9868.02319 3148.56686) (9857.91584 3159.87907) (9856.71097 3186.27455)))
("SF_MASONRY_AND_ARCH" 0 ((9932.12670 2179.48744) (9868.02319 2179.33281) (9856.71097 2171.94570)))
("SF_MASONRY_AND_ARCH" 0 ((9856.71097 1738.31165) (9875.41097 1739.51505) (9879.33541 1753.39367)))
("SF_MASONRY_AND_ARCH" 0 ((9860.48360 4098.79378) (9860.85158 4068.62749) (9871.79163 4068.62749) (9969.83314
4065.01109) (9977.07319 4068.78201) (9977.37557 4079.93925)))
("SF_MASONRY_AND_ARCH" 0 ((9860.48360 4098.79378) (9871.79581 4106.18020) (9966.06335 4106.48948) (9979.94197
4117.64706) (9988.83552 4138.91957) (10000.00000 4136.50034)))
("SF_MASONRY_AND_ARCH" 0 ((9860.48360 3740.57274) (9875.55871 3744.49853) (9890.64762 3766.96833)))
("SF_MASONRY_AND_ARCH" 0 ((9860.48360 2115.38462) (9860.48360 2126.69683)))
("SF_MASONRY_AND_ARCH" 0 ((9860.48360 2115.38462) (9871.79581 2111.76188) (9981.14050 2110.40995) (9988.52557
2100.30192) (9981.29378 2073.90622) (9981.30068 2055.05305) (9992.45758 2043.89548) (10135.74661 2047.51131)
(10180.99548 2043.74706) (10256.41120 2050.98563) (10267.72342 2047.80747) (10328.05430 2047.51131)))
("SF_MASONRY_AND_ARCH" 0 ((9860.48360 1855.20362) (9879.33541 1855.20362)))
("SF_MASONRY_AND_ARCH" 0 ((9868.02319 4343.89140) (9864.25339 4377.82805)))
("SF_MASONRY_AND_ARCH" 0 ((9868.02319 4193.06143) (9864.25339 4136.50034)))
("SF_MASONRY_AND_ARCH" 0 ((9890.64762 2635.74661) (9879.33541 2639.22093) (9864.25339 2635.74661)))
("SF_MASONRY_AND_ARCH" 0 ((9981.14536 1523.37952) (9969.83314 1526.99468) (9954.75113 1523.67500) (9943.43891
1526.85317) (9932.12670 1523.67500) (9864.25339 1523.37952)))
("SF_MASONRY_AND_ARCH" 0 ((9865.51075 531.67421) (9864.40113 554.29864) (9869.22805 572.78382) (9890.64762 573.15328)))
("SF_MASONRY_AND_ARCH" 0 ((9865.51075 531.67421) (9917.04468 539.06821) (9966.05645 539.36369) (9973.60577 542.98643)))
("SF_SOLAR" 0 ((9868.02319 8118.40113) (9868.02319 8133.48416)))
("SF_SOLAR" 0 ((9868.02319 8088.23529) (9868.02319 8069.38167)))
("SF_MASONRY_AND_ARCH" 0 ((9868.02319 4407.99355) (10049.01867 4407.98733) (10064.10351 4404.51957) (10105.57489
4408.14853) (10112.96753 4415.54208) (10113.12217 4445.70136)))
("SF_MASONRY_AND_ARCH" 0 ((9868.02319 4400.45249) (9868.02319 4407.99355)))
("SF_MASONRY_AND_ARCH" 0 ((9868.02319 4343.89140) (10060.33088 4343.89140)))
("SF_MASONRY_AND_ARCH" 0 ((9868.02319 4193.06143) (9883.10803 4196.83258) (9977.36934 4193.21640) (9983.86086
4196.98722) (9992.45758 4211.91595)))
("SF_MASONRY_AND_ARCH" 0 ((9868.02319 2767.72274) (9920.81448 2775.26369)))
("SF_MASONRY_AND_ARCH" 0 ((9871.79581 3061.84038) (9886.87783 3054.30554) (10045.24887 3058.06912)))
("SF_MASONRY_AND_ARCH" 0 ((9886.87783 2405.73156) (9871.79581 2405.73156)))
("SF_MASONRY_AND_ARCH" 0 ((9875.56561 6199.09502) (9909.50226 6195.33733) (9943.43891 6198.94695) (9966.06335
6195.32421)))
("SF_MASONRY_AND_ARCH" 0 ((9875.56561 6199.09502) (9879.33541 6210.40724)))
("SF_MASONRY_AND_ARCH" 0 ((9875.56561 5908.74819) (9879.33541 5878.58213)))
("SF_MASONRY_AND_ARCH" 0 ((9875.56561 5908.74819) (9883.10803 5923.83100)))
("SF_MASONRY_AND_ARCH" 0 ((9924.58428 3559.57794) (9875.56561 3555.80667)))
("SF_SOLAR" 0 ((9879.33541 8182.50385) (9879.33541 8174.96222)))
("SF_SOLAR" 0 ((9879.33541 8035.44502) (9879.33541 8046.75724)))
("SF_SOLAR" 0 ((9879.33541 8001.50837) (9879.33541 8016.59118)))
("SF_SOLAR" 0 ((9879.33541 7971.34231) (9879.33541 7986.42534)))
("SF_SOLAR" 0 ((9879.33541 7971.34231) (9905.73247 7971.34231)))
("SF_MASONRY_AND_ARCH" 0 ((9879.33541 5833.33326) (9879.33541 5855.95769)))
("SF_MASONRY_AND_ARCH" 0 ((10105.57975 5833.33326) (10090.49774 5829.56267) (9939.66912 5829.56923) (9917.04468
5833.33326) (9898.19005 5829.85894) (9879.33541 5833.33326)))
("SF_MASONRY_AND_ARCH" 0 ((9890.64762 3714.17839) (9885.67986 3695.47885) (9879.33541 3691.55396)))
("SF_MASONRY_AND_ARCH" 0 ((9879.33541 2488.68778) (9879.33541 2458.52161)))
("SF_MASONRY_AND_ARCH" 0 ((9886.87783 2405.73156) (9886.72319 2447.20939) (9879.33541 2458.52161)))
("SF_MASONRY_AND_ARCH" 0 ((9883.10803 1828.80871) (9879.33541 1855.20362)))
("SF_MASONRY_AND_ARCH" 0 ((9943.43891 1866.51584) (9890.64762 1862.59072) (9879.33541 1855.20362)))
("SF_MASONRY_AND_ARCH" 0 ((9901.95984 1251.88631) (9890.64762 1261.99367) (9879.33541 1263.19853)))
("SF_MASONRY_AND_ARCH" 0 ((9883.10803 5248.86878) (9966.06335 5248.86878)))
("SF_MASONRY_AND_ARCH" 0 ((9890.64762 3974.35939) (9886.87783 3985.67161)))
("SF_MASONRY_AND_ARCH" 0 ((9977.37557 4019.60826) (9969.61357 3990.64627) (9898.19005 3989.29367) (9886.87783
3985.67161)))
("SF_MASONRY_AND_ARCH" 0 ((9890.64762 3853.69536) (9886.87783 3804.67613)))
("SF_MASONRY_AND_ARCH" 0 ((9886.87783 2405.73156) (9898.19005 2405.73156)))
("SF_MASONRY_AND_ARCH" 0 ((9920.81448 1161.38857) (9894.42511 1161.53563) (9886.87783 1165.15837)))
("SF_MASONRY_AND_ARCH" 0 ((9886.87783 1010.55713) (9890.64762 991.70441)))
("SF_MASONRY_AND_ARCH" 0 ((9890.64762 4626.69683) (9992.45758 4622.92568)))
("SF_MASONRY_AND_ARCH" 0 ((10147.05882 3865.00713) (10116.89197 3853.69536) (10071.64310 3853.69536) (10045.24887
3853.69536) (10026.39423 3853.69536) (9981.14536 3853.69536) (9958.52093 3853.69536) (9943.43891 3853.69536) (9890.64762
3853.69536)))
("SF_MASONRY_AND_ARCH" 0 ((9890.64762 991.70441) (9898.19005 991.70441)))
("SF_MASONRY_AND_ARCH" 0 ((9894.42025 5520.36199) (9898.19005 5520.36199) (9901.95984 5527.90305)))
("SF_MASONRY_AND_ARCH" 0 ((9898.19005 5478.88428) (9898.19005 5441.17647)))
("SF_MASONRY_AND_ARCH" 0 ((10075.41572 5437.40532) (10060.33088 5441.17025) (9932.12670 5441.17025) (9913.27206
5437.56029) (9898.19005 5441.17647)))
("SF_MASONRY_AND_ARCH" 0 ((9950.98133 5098.03880) (9935.89649 5090.79423) (9898.19005 5094.26889)))
("SF_MASONRY_AND_ARCH" 0 ((9920.81448 2835.59604) (9898.19005 2835.59604)))
("SF_SOLAR" 0 ((9901.95984 8133.48416) (9901.95984 8122.17195)))
("SF_SOLAR" 0 ((9901.95984 8084.46448) (9901.95984 8069.38167)))
("SF_SOLAR" 0 ((9901.95984 8046.75724) (9901.95984 8031.67421)))
("SF_SOLAR" 0 ((9901.95984 8001.50837) (9901.95984 8012.82059)))
("SF_MASONRY_AND_ARCH" 0 ((9928.35690 5527.90305) (9901.95984 5527.90305)))
("SF_MASONRY_AND_ARCH" 0 ((9909.50226 5550.52749) (9903.15848 5542.98020) (9901.95984 5527.90305)))
("SF_MASONRY_AND_ARCH" 0 ((9901.95984 1251.88631) (9901.95984 1244.34389)))
("SF_MASONRY_AND_ARCH" 0 ((9901.95984 1251.88631) (9917.04468 1259.42590)))
("SF_MASONRY_AND_ARCH" 0 ((9913.27206 1233.03167) (9901.95984 1244.34389)))
("SF_SOLAR" 0 ((9905.73247 7982.65452) (9905.73247 7971.34231)))
("SF_SOLAR" 0 ((9917.04468 7967.57172) (9905.73247 7971.34231)))
("SF_MASONRY_AND_ARCH" 0 ((9905.73247 4264.70588) (9917.04468 4268.47014) (10003.76980 4268.32206) (10018.85464
4260.93473)))
("SF_MASONRY_AND_ARCH" 0 ((9913.27206 810.70984) (9905.73247 810.70984)))
("SF_MASONRY_AND_ARCH" 0 ((9909.50226 4856.71233) (9913.27206 4890.64898)))
("SF_MASONRY_AND_ARCH" 0 ((9924.58428 3148.56686) (9913.27206 3148.56686) (9909.50226 3152.33812)))
("SF_MASONRY_AND_ARCH" 0 ((9913.27206 810.70984) (9909.50226 844.64649)))
("SF_MASONRY_AND_ARCH" 0 ((9909.50226 844.64649) (9932.12670 848.41007) (10131.97681 848.41629)))
("SF_MASONRY_AND_ARCH" 0 ((9909.50226 573.15328) (9924.58428 573.15328)))
("SF_MASONRY_AND_ARCH" 0 ((10128.20419 4894.41889) (9947.20871 4894.41267) (9913.27206 4890.64898)))
("SF_MASONRY_AND_ARCH" 0 ((9913.27206 2330.31674) (10194.19400 2334.08722)))
("SF_MASONRY_AND_ARCH" 0 ((9913.27206 810.70984) (9984.91041 810.56143) (9992.45758 806.93722)))
("SF_MASONRY_AND_ARCH" 0 ((9920.81448 2835.59604) (9924.58428 2820.51256) (9920.81448 2775.26369)))
("SF_MASONRY_AND_ARCH" 0 ((9920.81448 2835.59604) (9924.57941 2850.67873) (9921.11063 2892.15713) (9924.58428
2944.94695)))
("SF_MASONRY_AND_ARCH" 0 ((9992.45758 2767.72274) (9973.60577 2771.48631) (9939.66912 2768.01199) (9920.81448
2775.26369)))
("SF_MASONRY_AND_ARCH" 0 ((9988.68778 2631.97613) (9969.83314 2626.53337) (9920.81448 2628.20486)))
("SF_MASONRY_AND_ARCH" 0 ((9920.81448 1798.64253) (9962.29355 1806.17805) (10128.20419 1806.17805) (10143.28145
1802.70928) (10150.82862 1806.18495)))
("SF_MASONRY_AND_ARCH" 0 ((10101.80995 2944.94695) (10082.95532 2941.17647) (9924.58428 2944.94695)))
("SF_MASONRY_AND_ARCH" 0 ((9924.58428 2273.75566) (9935.89649 2269.99140) (9969.83314 2272.55769) (9988.68778
2266.21391)))
("SF_MASONRY_AND_ARCH" 0 ((9935.89649 1987.17975) (9939.51380 1941.93088) (9935.74321 1934.54378) (9924.58428
1930.61867)))
("SF_MASONRY_AND_ARCH" 0 ((9924.58428 953.99604) (9977.37557 961.24231) (9988.68778 957.76867)))
("SF_MASONRY_AND_ARCH" 0 ((9939.66912 1089.74265) (9932.12670 1089.74265)))
("SF_SOLAR" 0 ((9943.43891 8141.02557) (9935.89649 8141.02557)))
("SF_SOLAR" 0 ((9935.89649 8141.02557) (9932.42285 8129.71335) (9935.89649 8118.40113)))
("SF_SOLAR" 0 ((9939.66912 8178.73303) (9932.27511 8159.87941) (9935.89649 8141.02557)))
("SF_SOLAR" 0 ((9954.75113 8110.85973) (9947.20385 8117.20351) (9935.89649 8118.40113)))
("SF_SOLAR" 0 ((9935.89649 8073.15226) (9935.89649 8118.40113)))
("SF_MASONRY_AND_ARCH" 0 ((9935.89649 3408.74785) (9981.14536 3408.60011) (9992.45758 3404.97738)))
("SF_MASONRY_AND_ARCH" 0 ((9981.14536 2405.73156) (9935.89649 2405.73156)))
("SF_MASONRY_AND_ARCH" 0 ((9935.89649 1987.17975) (9962.29355 1987.32817) (9981.14536 1994.72070)))
("SF_MASONRY_AND_ARCH" 0 ((9996.23020 991.70441) (9973.60577 991.70441) (9943.44581 991.70441) (9935.89649 991.70441)))
("SF_MASONRY_AND_ARCH" 0 ((9943.43891 1866.51584) (9939.66912 1892.91075)))
("SF_MASONRY_AND_ARCH" 0 ((9939.66912 1229.26188) (9943.43891 1225.48925) (9954.75113 1225.48925)))
("SF_MASONRY_AND_ARCH" 0 ((9943.43891 1866.51584) (10033.93665 1860.17206) (10071.64310 1866.50962) (10143.28903
1866.36810) (10154.60124 1862.74536)))
("SF_MASONRY_AND_ARCH" 0 ((9943.43891 82.95532) (9950.98133 90.49774)))
("SF_SOLAR" 0 ((9947.20871 7948.71799) (9962.29355 7948.71799)))
("SF_SOLAR" 0 ((9954.75113 7926.09355) (9947.20871 7948.71799)))
("SF_SOLAR" 0 ((9954.75113 8065.61086) (9947.35713 8064.40656) (9943.59355 8058.06278) (9947.20871 7948.71799)))
("SF_MASONRY_AND_ARCH" 0 ((9950.98133 4777.52681) (9947.20871 4769.98450)))
("SF_MASONRY_AND_ARCH" 0 ((10105.57975 1353.69627) (10101.58971 1347.34491) (10086.72794 1342.53111) (10003.76980
1342.67952) (9984.91799 1346.15385) (9954.75803 1345.99921) (9947.20871 1342.38405)))
("SF_MASONRY_AND_ARCH" 0 ((9947.20871 177.22568) (9947.35713 139.51640) (9958.52851 121.86799) (10003.76980 116.89887)
(10090.49774 116.89887) (10128.20419 120.66459)))
("SF_MASONRY_AND_ARCH" 0 ((9947.20871 177.22568) (9973.60577 180.99548) (10003.76980 177.23054) (10049.01867 180.84774)
(10060.33088 177.22568)))
("SF_MASONRY_AND_ARCH" 0 ((9950.98133 4777.52681) (9962.29355 4781.14887) (10124.43439 4781.30362) (10147.05882
4785.06787)))
("SF_MASONRY_AND_ARCH" 0 ((10154.60124 1191.55260) (10139.51640 1184.16629) (10049.01867 1187.77658) (10033.93665
1184.16007) (9973.75905 1182.80814) (9966.21799 1153.84615) (9969.68609 1138.76414) (9968.77749 1104.82749) (9962.14514
1094.71867) (9950.98133 1093.51527)))
("SF_MASONRY_AND_ARCH" 0 ((9950.98133 573.15328) (9954.75113 576.92308) (9966.06335 576.92308)))
("SF_MASONRY_AND_ARCH" 0 ((9950.98133 256.41120) (9966.06335 256.41120)))
("SF_MASONRY_AND_ARCH" 0 ((9966.06335 5641.02557) (9954.75113 5674.96222)))
("SF_MASONRY_AND_ARCH" 0 ((9954.75113 5674.96222) (9964.86538 5705.12828) (9962.29355 5731.52330)))
("SF_MASONRY_AND_ARCH" 0 ((9966.06335 6116.13869) (9958.52093 6112.36810)))
("SF_MASONRY_AND_ARCH" 0 ((9958.52093 52.79129) (9966.06335 49.01867)))
("SF_MASONRY_AND_ARCH" 0 ((10248.86878 4973.60441) (10139.51640 4973.59819) (10116.89197 4969.83450) (10026.39423
4969.84072) (10007.54242 4973.59819) (9969.84072 4970.13043) (9962.29355 4973.60441)))
("SF_MASONRY_AND_ARCH" 0 ((10196.07749 3706.63609) (10177.22568 3710.40102) (9947.36403 3709.20271) (9943.59355
3702.85928) (9944.64378 3691.70792) (9962.29355 3687.78281)))
("SF_SOLAR" 0 ((9964.17794 8061.84016) (9966.06335 8061.84016) (9967.94876 8061.84016)))
("SF_MASONRY_AND_ARCH" 0 ((9966.06335 6116.13869) (9969.83314 6131.22172) (9969.68609 6180.24140) (9966.06335
6195.32421)))
("SF_MASONRY_AND_ARCH" 0 ((9996.23020 6210.40724) (9977.37557 6205.43224) (9966.06335 6195.32421)))
("SF_MASONRY_AND_ARCH" 0 ((9966.06335 6116.13869) (9973.75283 6101.06244) (9984.91799 6093.67545) (10003.76980
6097.27851) (10180.99548 6097.28507) (10196.07749 6093.51425)))
("SF_MASONRY_AND_ARCH" 0 ((9966.06335 5641.02557) (9958.66934 5622.17195) (9959.72579 5554.29864) (9969.83314
5544.19717) (9988.68778 5546.60260) (10011.31222 5543.13450) (10026.39423 5546.74446) (10075.41572 5542.99265)
(10101.80995 5546.75758)))
("SF_MASONRY_AND_ARCH" 0 ((9966.06335 5641.02557) (9988.68778 5644.78982) (10049.01380 5641.18020) (10056.56109
5644.79638)))
("SF_MASONRY_AND_ARCH" 0 ((9973.60577 5199.84876) (9966.06335 5248.86878)))
("SF_MASONRY_AND_ARCH" 0 ((10022.62443 5252.63993) (9973.61063 5252.49152) (9966.06335 5248.86878)))
("SF_MASONRY_AND_ARCH" 0 ((9973.60577 3159.87907) (9966.06335 3148.56686)))
("SF_MASONRY_AND_ARCH" 0 ((9966.06335 2865.76165) (9977.37557 2865.76165) (10045.24887 2865.76165) (10064.10351
2865.76165) (10128.20419 2865.76165)))
("SF_MASONRY_AND_ARCH" 0 ((9966.06335 576.92308) (9973.60577 542.98643)))
("SF_MASONRY_AND_ARCH" 0 ((9966.06335 576.92308) (9969.83314 595.77771) (9969.83314 603.31731) (9969.68609 667.42081)
(9966.07579 682.50283) (9969.83314 697.58767)))
("SF_MASONRY_AND_ARCH" 0 ((10098.04016 256.41120) (10000.00000 256.40430) (9981.14536 252.65238) (9966.06335
256.41120)))
("SF_MASONRY_AND_ARCH" 0 ((9969.83314 275.26301) (9966.06335 256.41120)))
("SF_MASONRY_AND_ARCH" 0 ((9969.83314 6255.65611) (9988.68778 6255.65611)))
("SF_MASONRY_AND_ARCH" 0 ((9969.83314 6018.09955) (10011.31222 6014.32873)))
("SF_MASONRY_AND_ARCH" 0 ((9969.83314 6018.09955) (9969.98156 6067.11267) (9973.60577 6074.66063)))
("SF_MASONRY_AND_ARCH" 0 ((9973.60577 5199.84876) (9969.83314 5180.99548)))
("SF_MASONRY_AND_ARCH" 0 ((9969.83314 3559.57794) (9992.45758 3567.11889)))
("SF_MASONRY_AND_ARCH" 0 ((9969.83314 1606.33484) (9979.94197 1595.02885) (9981.14536 1587.48020)))
("SF_MASONRY_AND_ARCH" 0 ((9969.83405 3186.27455) (9971.71946 3186.27455) (9973.60486 3186.27455)))
("SF_MASONRY_AND_ARCH" 0 ((9988.68778 5199.84876) (9973.60577 5199.84876)))
("SF_MASONRY_AND_ARCH" 0 ((9988.68778 2213.42410) (9983.86086 2228.35215) (9973.60577 2232.27726)))
("SF_MASONRY_AND_ARCH" 0 ((10165.91346 539.21663) (10105.57975 539.36369) (10086.72794 542.98643) (9992.45758 539.22149)
(9973.60577 542.98643)))
("SF_SOLAR" 0 ((9977.37557 7911.01052) (9984.62104 7888.39276) (9981.14536 7880.84468)))
("SF_MASONRY_AND_ARCH" 0 ((9977.37557 4724.73563) (9995.39333 4722.22896) (10011.31222 4728.50679)))
("SF_MASONRY_AND_ARCH" 0 ((9977.37557 4019.60826) (9977.37557 4030.92048)))
("SF_MASONRY_AND_ARCH" 0 ((9977.37557 4019.60826) (10045.24887 4019.75611) (10064.10351 4023.37817) (10188.53790
4023.37195) (10207.38971 4019.61448) (10263.95079 4023.37195) (10279.03563 4019.90419) (10313.27398 4023.67466)
(10318.08778 4019.90419) (10324.28450 3996.98382)))
("SF_MASONRY_AND_ARCH" 0 ((9977.37557 3684.01165) (9984.91799 3680.24174)))
("SF_SOLAR" 0 ((9981.14536 8220.21109) (9984.91799 8227.75271)))
("SF_MASONRY_AND_ARCH" 0 ((9981.14536 5064.10215) (9984.91799 4996.22885)))
("SF_MASONRY_AND_ARCH" 0 ((9981.14536 2021.11640) (9981.14536 1994.72070)))
("SF_MASONRY_AND_ARCH" 0 ((9981.14536 1994.72070) (9988.69468 1991.09796) (10030.16686 1990.80249) (10041.47907
1987.17975)))
("SF_MASONRY_AND_ARCH" 0 ((9981.14536 1564.85577) (9981.14536 1587.48020)))
("SF_MASONRY_AND_ARCH" 0 ((9981.14536 1587.48020) (10000.00000 1591.10441) (10124.43439 1595.02262)))
("SF_MASONRY_AND_ARCH" 0 ((9981.14536 1523.37952) (10064.10351 1523.37952)))
("SF_MASONRY_AND_ARCH" 0 ((9981.14536 1523.37952) (9981.14536 1515.83710)))
("SF_MASONRY_AND_ARCH" 0 ((9981.14536 1440.42138) (9981.14536 1493.21267)))
("SF_MASONRY_AND_ARCH" 0 ((9981.14536 1440.42138) (9996.23020 1436.79932) (10071.64310 1436.65158)))
("SF_MASONRY_AND_ARCH" 0 ((9992.45758 4566.36459) (9984.91799 4566.36459)))
("SF_MASONRY_AND_ARCH" 0 ((9984.91799 3672.69943) (9984.91799 3680.24174)))
("SF_MASONRY_AND_ARCH" 0 ((10018.85464 3684.01165) (9984.91799 3680.24174)))
("SF_MASONRY_AND_ARCH" 0 ((9984.91799 3597.28507) (9992.30430 3589.73710) (9992.45758 3567.11889)))
("SF_MASONRY_AND_ARCH" 0 ((9984.91799 3597.28507) (9988.68778 3608.59729)))
("SF_MASONRY_AND_ARCH" 0 ((9996.23020 1266.96833) (9984.91799 1266.96833)))
("SF_MASONRY_AND_ARCH" 0 ((9988.68778 6255.65611) (10000.00000 6240.57308)))
("SF_MASONRY_AND_ARCH" 0 ((10263.95079 6308.44638) (10011.31222 6308.29163) (9993.66244 6293.36357) (9992.31052
6263.20407) (9988.68778 6255.65611)))
("SF_MASONRY_AND_ARCH" 0 ((9988.68778 4596.53133) (9992.45758 4622.92568)))
("SF_MASONRY_AND_ARCH" 0 ((9988.68778 4234.54038) (9992.45758 4211.91595)))
("SF_MASONRY_AND_ARCH" 0 ((10022.62443 2624.43439) (9988.68778 2631.97613)))
("SF_MASONRY_AND_ARCH" 0 ((9992.45758 2677.22500) (9988.83552 2669.67636) (9988.68778 2631.97613)))
("SF_MASONRY_AND_ARCH" 0 ((9992.45758 2258.67296) (9988.68778 2266.21391)))
("SF_MASONRY_AND_ARCH" 0 ((10003.76980 2269.98518) (9988.68778 2266.21391)))
("SF_MASONRY_AND_ARCH" 0 ((9988.68778 2198.34061) (9988.68778 2175.71618)))
("SF_SOLAR" 0 ((9990.57319 7911.01052) (9992.45848 7911.01052) (9994.34389 7911.01052)))
("SF_SOLAR" 0 ((9992.45758 8027.90339) (10000.00000 8027.90339)))
("SF_SOLAR" 0 ((9992.45758 7990.19615) (10000.00000 7993.96686)))
("SF_MASONRY_AND_ARCH" 0 ((9996.23020 4634.23790) (9992.60600 4645.55079) (9992.45758 4679.48676)))
("SF_MASONRY_AND_ARCH" 0 ((9996.23020 4634.23790) (9992.45758 4622.92568)))
("SF_MASONRY_AND_ARCH" 0 ((10139.51640 4215.68586) (9992.45758 4211.91595)))
("SF_MASONRY_AND_ARCH" 0 ((9992.45758 3567.11889) (10000.00000 3563.34842)))
("SF_MASONRY_AND_ARCH" 0 ((9992.45758 3288.08473) (9992.45758 3325.79186)))
("SF_MASONRY_AND_ARCH" 0 ((10199.85011 3333.33360) (10143.28903 3333.18586) (10105.57975 3326.98982) (10090.49774
3329.54921) (10049.01867 3325.79808) (10018.85464 3329.55611) (9992.45758 3325.79186)))
("SF_MASONRY_AND_ARCH" 0 ((9992.45758 3288.08473) (9992.46448 3197.58699) (9996.23020 3186.27455)))
("SF_MASONRY_AND_ARCH" 0 ((9992.45758 3288.08473) (10022.62443 3291.84830) (10045.24887 3288.09095) (10143.28903
3288.08473)))
("SF_MASONRY_AND_ARCH" 0 ((9992.45758 2767.72274) (9988.69468 2745.09830) (9993.66244 2718.85724) (10000.00000
2715.23450) (10007.54242 2718.70260)))
("SF_MASONRY_AND_ARCH" 0 ((10018.85464 2767.72274) (10007.54242 2771.33857) (9992.45758 2767.72274)))
("SF_MASONRY_AND_ARCH" 0 ((9992.45758 806.93722) (9992.45758 754.14876)))
("SF_MASONRY_AND_ARCH" 0 ((9992.45758 806.93722) (10000.00690 810.56143) (10052.79129 810.85690) (10086.72794 818.10238)
(10116.88710 818.10238) (10124.43439 814.47964)))
("SF_MASONRY_AND_ARCH" 0 ((10218.70192 52.79129) (9992.45758 52.79129)))
("SF_SOLAR" 0 ((9992.45848 8061.84016) (9994.34389 8061.84016) (9996.22930 8061.84016)))
("SF_MASONRY_AND_ARCH" 0 ((9996.23020 6210.40724) (10011.31222 6206.63654) (10192.30769 6206.63654) (10203.61991
6206.63654)))
("SF_MASONRY_AND_ARCH" 0 ((9996.23020 6210.40724) (10000.00000 6217.94864)))
("SF_MASONRY_AND_ARCH" 0 ((10241.32636 4634.23790) (10143.28903 4634.23167) (10124.43439 4630.47421) (10079.18552
4634.23167) (10056.56109 4630.46799) (9996.23020 4634.23790)))
("SF_SOLAR" 0 ((11960.78473 7914.78133) (11959.58620 7903.46900) (11936.96176 7858.22025) (11926.84808 7848.11233)
(11813.72590 7846.91459) (11791.10147 7850.67873) (11764.70588 7846.91459) (10237.55656 7848.11233) (10207.38971
7869.37783) (10018.85464 7869.53903) (10003.76980 7873.30317)))
("SF_SOLAR" 0 ((10018.85464 7914.78133) (10001.06256 7892.15690) (10003.76980 7873.30317)))
("SF_MASONRY_AND_ARCH" 0 ((10003.76980 6331.07081) (10003.91821 6387.62534) (10007.54242 6398.94423)))
("SF_MASONRY_AND_ARCH" 0 ((10007.54242 6398.94423) (10018.85464 6398.94423) (10271.49321 6398.93756) (10286.57523
6391.40271)))
("SF_MASONRY_AND_ARCH" 0 ((10007.54242 5765.45995) (10052.79129 5770.90238) (10105.57489 5766.65747) (10113.12217
5769.23077)))
("SF_SOLAR" 0 ((10011.31222 8227.75271) (10015.08201 8220.21109)))
("SF_MASONRY_AND_ARCH" 0 ((10011.31222 3981.90045) (10082.95532 3982.04853) (10094.26753 3985.37511) (10105.57975
3981.90045)))
("SF_MASONRY_AND_ARCH" 0 ((10011.31222 1070.89084) (10056.56109 1070.74242) (10071.64310 1067.11821)))
("SF_MASONRY_AND_ARCH" 0 ((10011.31222 991.70441) (10071.64310 987.93269)))
("SF_MASONRY_AND_ARCH" 0 ((10015.08201 5305.42986) (10022.62443 5316.74208)))
("SF_SOLAR" 0 ((10018.85464 7914.78133) (10037.70645 7911.15860) (10184.76527 7908.43756) (10471.34333 7911.01708)
(10486.42534 7914.63326) (10535.08292 7915.14989) (10591.85803 8133.48416) (10592.00509 8163.65000)))
("SF_SOLAR" 0 ((10018.85464 7914.78133) (10011.31844 7948.71799) (10011.46063 8193.81606) (10016.13914 8204.98009)
(10030.16686 8212.52161) (10588.23529 8212.66312) (10641.02658 8208.89898) (10663.65102 8212.66968) (11070.89084
8212.66968) (11085.97285 8212.66968) (11101.05486 8212.66968) (11259.42590 8212.66968) (11327.29921 8205.14140)
(11357.46606 8212.66312) (11572.39819 8212.66312) (11598.79378 8208.89887) (11659.12477 8209.04695) (11674.20814
8212.66312) (11794.87138 8212.66312) (11813.72590 8208.90554) (11843.89140 8212.66312) (11866.51584 8208.89910)
(11889.14027 8212.66312) (12119.15577 8212.66312) (12134.68937 8208.75079) (12145.55011 8216.44050)))
("SF_SOLAR" 0 ((10022.62443 8171.19163) (10037.70645 8171.19163)))
("SF_SOLAR" 0 ((10030.16686 8061.84016) (10022.62443 8061.84016)))
("SF_SOLAR" 0 ((10022.62443 7993.96686) (10030.16686 7993.96686)))
("SF_SOLAR" 0 ((10037.70645 7948.71799) (10022.62443 7948.71799)))
("SF_MASONRY_AND_ARCH" 0 ((10022.62443 3408.74785) (10033.93665 3404.98428) (10049.01867 3408.74785)))
("SF_MASONRY_AND_ARCH" 0 ((10026.39423 2405.73156) (10030.16686 2405.73156) (10041.47907 2405.73156)))
("SF_SOLAR" 0 ((10037.70645 8141.02557) (10030.16686 8141.02557)))
("SF_SOLAR" 0 ((10041.47907 8118.40113) (10030.16686 8114.63054)))
("SF_MASONRY_AND_ARCH" 0 ((10067.87330 3680.24174) (10041.48394 3680.38959) (10033.93665 3684.01165)))
("SF_MASONRY_AND_ARCH" 0 ((10033.93665 2515.08269) (10033.93665 2488.68778)))
("SF_MASONRY_AND_ARCH" 0 ((10033.93665 2515.08269) (10090.49774 2522.62443)))
("SF_MASONRY_AND_ARCH" 0 ((10109.35238 2269.98518) (10086.72794 2273.60102) (10033.93665 2269.98518)))
("SF_MASONRY_AND_ARCH" 0 ((10109.35238 2168.17523) (10098.04016 2179.33281) (10033.93665 2179.48744)))
("SF_SOLAR" 0 ((10037.70645 8171.19163) (10044.05090 8163.64344) (10045.24887 8144.79638)))
("SF_SOLAR" 0 ((10037.70645 8171.19163) (10041.47907 8182.50385)))
("SF_SOLAR" 0 ((10037.70645 8141.02557) (10041.47907 8118.40113)))
("SF_SOLAR" 0 ((10037.70645 8141.02557) (10045.24887 8144.79638)))
("SF_SOLAR" 0 ((10199.85011 7948.71799) (10037.70645 7948.71799)))
("SF_SOLAR" 0 ((10041.47907 7926.09355) (10037.70645 7948.71799)))
("SF_SOLAR" 0 ((10037.70645 7948.71799) (10041.47907 7956.25939) (10037.86176 7975.11312) (10041.47907 7993.96686)))
("SF_MASONRY_AND_ARCH" 0 ((10131.97681 5950.22624) (10052.79129 5950.37432) (10037.70645 5953.99706)))
("SF_MASONRY_AND_ARCH" 0 ((10037.70645 5953.99706) (10041.47907 5987.93371)))
("SF_MASONRY_AND_ARCH" 0 ((10222.47455 3631.22172) (10192.30769 3638.60882) (10158.37104 3634.99287) (10135.74661
3638.75656) (10056.56109 3638.75656) (10037.70645 3634.99287)))
("SF_MASONRY_AND_ARCH" 0 ((10037.70645 2767.72274) (10045.25577 2771.34548) (10071.64310 2771.49321)))
("SF_MASONRY_AND_ARCH" 0 ((10252.63857 2628.20486) (10233.78676 2624.44061) (10037.70645 2624.43439)))
("SF_SOLAR" 0 ((10041.47907 8118.40113) (10041.47907 8061.84016)))
("SF_SOLAR" 0 ((10184.76527 8061.84016) (10041.47907 8061.84016)))
("SF_SOLAR" 0 ((10041.47907 8027.90339) (10041.47907 8061.84016)))
("SF_SOLAR" 0 ((10177.22568 8027.90339) (10041.47907 8027.90339)))
("SF_SOLAR" 0 ((10041.47907 7993.96686) (10041.47907 8027.90339)))
("SF_SOLAR" 0 ((10175.33937 7993.96686) (10041.47907 7993.96686)))
("SF_MASONRY_AND_ARCH" 0 ((10041.47907 4140.27149) (10105.57975 4140.41957) (10120.66459 4144.02952) (10139.51640
4140.27771) (10226.24434 4140.27149) (10233.78676 4140.27149) (10282.80543 4144.04265)))
("SF_MASONRY_AND_ARCH" 0 ((10120.66459 3186.27455) (10109.35238 3186.27455) (10041.47907 3186.27455)))
("SF_MASONRY_AND_ARCH" 0 ((10196.07749 2722.47387) (10041.47907 2718.70260)))
("SF_SOLAR" 0 ((10194.19400 8141.02568) (10067.87330 8141.02568) (10045.24887 8144.79638)))
("SF_MASONRY_AND_ARCH" 0 ((10060.33088 6018.09955) (10049.38812 6013.96686) (10045.24887 5999.24593)))
("SF_MASONRY_AND_ARCH" 0 ((10147.05882 4724.73563) (10045.24887 4728.50679)))
("SF_MASONRY_AND_ARCH" 0 ((10045.24887 4264.70588) (10064.10351 4254.59785) (10082.95532 4253.39367) (10090.49774
4253.39367) (10139.51640 4245.85260)))
("SF_MASONRY_AND_ARCH" 0 ((10045.24887 2156.86301) (10056.56109 2160.62726) (10086.72794 2157.01765) (10109.35238
2168.17523)))
("SF_SOLAR" 0 ((10188.53790 8099.54751) (10064.10351 8099.54095) (10049.01867 8095.77670)))
("SF_SOLAR" 0 ((10052.79129 8167.42081) (10064.10351 8163.65656) (10188.53790 8163.65000)))
("SF_MASONRY_AND_ARCH" 0 ((10056.56109 5252.63993) (10116.89197 5252.78778) (10128.20419 5256.11391) (10165.91346
5252.63993)))
("SF_MASONRY_AND_ARCH" 0 ((10060.33088 4370.28699) (10060.33088 4343.89140)))
("SF_MASONRY_AND_ARCH" 0 ((10395.92760 4343.89140) (10388.38032 4340.27523) (10331.82410 4343.88518) (10309.19966
4340.12025) (10263.95079 4340.26867) (10252.63857 4343.73676) (10233.78676 4340.12715) (10075.41572 4340.12715)
(10060.33088 4343.89140)))
("SF_MASONRY_AND_ARCH" 0 ((10064.10351 4317.49581) (10060.47930 4309.94853) (10060.33088 4287.33032)))
("SF_MASONRY_AND_ARCH" 0 ((10071.64310 1067.11821) (10067.87330 1059.57862)))
("SF_SOLAR" 0 ((10071.64310 8133.48416) (10071.64310 8122.17195)))
("SF_MASONRY_AND_ARCH" 0 ((10263.95079 1990.95023) (10211.16233 1994.71448) (10192.30769 1990.95645) (10086.72794
1990.80249) (10071.64310 1987.17975)))
("SF_MASONRY_AND_ARCH" 0 ((10071.64310 1266.96833) (10094.26267 1267.11606) (10101.80995 1270.73812)))
("SF_MASONRY_AND_ARCH" 0 ((10139.51640 1074.66063) (10113.12217 1074.51290) (10071.64310 1067.11821)))
("SF_MASONRY_AND_ARCH" 0 ((10086.72794 991.70532) (10082.95532 987.93269) (10071.64310 987.93269)))
("SF_MASONRY_AND_ARCH" 0 ((10086.72794 950.22624) (10072.84796 961.53846) (10071.64310 987.93269)))
("SF_SOLAR" 0 ((10079.18552 8039.21561) (10082.95532 8050.52783)))
("SF_SOLAR" 0 ((10079.18552 8005.27896) (10079.18552 8016.59118)))
("SF_SOLAR" 0 ((10082.95532 7971.34231) (10079.18552 7982.65452)))
("SF_SOLAR" 0 ((10082.95532 8088.23529) (10079.18552 8084.46448) (10082.95532 8073.15226)))
("SF_SOLAR" 0 ((10082.95532 7971.34231) (10105.57975 7971.34231)))
("SF_SOLAR" 0 ((10082.95532 7963.80090) (10082.95532 7971.34231)))
("SF_MASONRY_AND_ARCH" 0 ((10082.95532 1436.65158) (10230.01414 1434.97998) (10248.86878 1440.12590) (10282.80543
1436.65781) (10297.88744 1440.27432) (10343.13631 1440.42138)))
("SF_MASONRY_AND_ARCH" 0 ((10124.43439 177.22568) (10105.57975 180.99548) (10082.95532 177.22568)))
("SF_MASONRY_AND_ARCH" 0 ((10086.72794 3548.26572) (10105.57975 3548.26572)))
("SF_MASONRY_AND_ARCH" 0 ((10086.72794 3408.74785) (10124.43439 3408.74785)))
("SF_MASONRY_AND_ARCH" 0 ((10186.65158 2405.73156) (10094.27511 2405.73156) (10086.72794 2405.73156)))
("SF_MASONRY_AND_ARCH" 0 ((10150.82862 2522.62443) (10135.74661 2518.85396) (10090.49774 2522.62443)))
("SF_MASONRY_AND_ARCH" 0 ((10090.49774 2522.62443) (10090.64548 2537.70713) (10098.19344 2562.89864) (10150.82862
2564.10283)))
("SF_MASONRY_AND_ARCH" 0 ((10094.26753 1523.37952) (10139.51640 1526.85317) (10154.60124 1523.38439) (10335.59672
1521.85498) (10358.22115 1533.63462) (10388.38518 1534.69174)))
("SF_MASONRY_AND_ARCH" 0 ((10094.26753 361.99095) (10131.97681 354.44853)))
("SF_MASONRY_AND_ARCH" 0 ((10094.26753 361.99095) (10094.42285 403.47002) (10101.80995 418.55204)))
("SF_MASONRY_AND_ARCH" 0 ((10098.04016 3046.75690) (10105.57975 3058.06912)))
("SF_MASONRY_AND_ARCH" 0 ((10098.04016 429.86425) (10101.80995 418.55204)))
("SF_MASONRY_AND_ARCH" 0 ((10101.80995 6021.87036) (10109.35724 6019.29717) (10192.30769 6025.64095)))
("SF_MASONRY_AND_ARCH" 0 ((10105.57975 5889.89434) (10101.80995 5897.43597)))
("SF_MASONRY_AND_ARCH" 0 ((10101.80995 5546.75758) (10116.89197 5543.13450) (10192.30769 5541.31482) (10226.24434
5543.13450) (10241.32636 5550.52749)))
("SF_MASONRY_AND_ARCH" 0 ((10101.80995 5546.75758) (10106.78462 5588.23529) (10116.89197 5597.29355) (10218.70192
5599.69559) (10237.55656 5607.08857)))
("SF_MASONRY_AND_ARCH" 0 ((10101.80995 2944.94695) (10120.66459 2941.17647) (10214.93213 2941.18269) (10241.32636
2944.94695)))
("SF_MASONRY_AND_ARCH" 0 ((10109.35238 3009.04977) (10098.18790 2978.88360) (10101.80995 2944.94695)))
("SF_MASONRY_AND_ARCH" 0 ((10211.16233 418.55204) (10101.80995 418.55204)))
("SF_SOLAR" 0 ((10105.57975 8122.17195) (10105.57975 8133.48416)))
("SF_SOLAR" 0 ((10105.57975 8073.15226) (10105.57975 8088.23529)))
("SF_SOLAR" 0 ((10105.57975 8035.44502) (10105.57975 8050.52783)))
("SF_SOLAR" 0 ((10105.57975 8005.27896) (10105.57975 8016.59118)))
("SF_SOLAR" 0 ((10105.57975 7982.65452) (10105.57975 7971.34231)))
("SF_SOLAR" 0 ((10128.20419 7971.34231) (10105.57975 7971.34231)))
("SF_SOLAR" 0 ((10105.57975 7960.03020) (10105.57975 7971.34231)))
("SF_SOLAR" 0 ((10105.57975 7926.09355) (10105.57975 7937.40577)))
("SF_MASONRY_AND_ARCH" 0 ((10105.57975 5833.33326) (10105.57975 5855.95769)))
("SF_MASONRY_AND_ARCH" 0 ((10105.57975 5833.33326) (10124.43439 5822.02104)))
("SF_MASONRY_AND_ARCH" 0 ((10105.57975 5629.71335) (10102.32636 5638.09050) (10109.28744 5643.66267) (10162.14084
5644.79638)))
("SF_MASONRY_AND_ARCH" 0 ((10173.45305 3469.08020) (10105.57975 3472.85068)))
("SF_MASONRY_AND_ARCH" 0 ((10241.32636 3503.01686) (10218.70192 3506.78111) (10116.89197 3506.63269) (10106.78462
3499.23937) (10105.57975 3472.85068)))
("SF_MASONRY_AND_ARCH" 0 ((10109.35238 3009.04977) (10105.57975 3020.36199)))
("SF_MASONRY_AND_ARCH" 0 ((10105.57975 2771.49321) (10124.43439 2778.73869) (10154.60124 2771.64785) (10226.24434
2775.26369) (10248.86878 2771.49321)))
("SF_ARCHITECTURE" 0 ((10320.51188 6828.80848) (10305.42986 6828.80848) (10120.66459 6828.80848) (10109.35238
6828.80848)))
("SF_ARCHITECTURE" 0 ((10113.12217 7579.18552) (10109.35147 7530.16595) (10109.35238 6828.80848)))
("SF_MASONRY_AND_ARCH" 0 ((10109.35238 3009.04977) (10113.12217 3005.27930) (10124.43439 3005.27930)))
("SF_MASONRY_AND_ARCH" 0 ((10109.35238 2168.17523) (10124.43439 2171.79796) (10154.60124 2168.47138) (10177.22568
2171.93948) (10241.32636 2160.92964) (10279.02805 2165.60814) (10285.37183 2171.95260) (10286.57523 2194.57014)))
("SF_MASONRY_AND_ARCH" 0 ((10109.35238 991.70532) (10143.28903 991.70532)))
("SF_ARCHITECTURE" 0 ((10113.12217 7579.18552) (10162.14084 7571.65057) (10320.51278 7571.64400)))
("SF_MASONRY_AND_ARCH" 0 ((10113.12217 5437.40532) (10158.37104 5440.87998) (10184.76041 5437.55373) (10192.30769
5441.17647)))
("SF_MASONRY_AND_ARCH" 0 ((10113.12217 4513.57466) (10114.32704 4483.41538) (10124.43439 4476.02183) (10188.53790
4483.39604) (10207.38971 4479.64423) (10312.97229 4479.63801)))
("SF_MASONRY_AND_ARCH" 0 ((10113.12217 4513.57466) (10120.66946 4517.19740) (10211.16233 4517.35204) (10230.01414
4521.10950) (10339.36652 4517.34581)))
("SF_MASONRY_AND_ARCH" 0 ((10124.43439 1346.15385) (10150.82862 1338.61143)))
("SF_SOLAR" 0 ((10128.20419 8122.17195) (10128.20419 8133.48416)))
("SF_SOLAR" 0 ((10128.20419 8088.23529) (10128.20419 8069.38167)))
("SF_SOLAR" 0 ((10128.20419 8050.52783) (10128.20419 8039.21561)))
("SF_SOLAR" 0 ((10128.20419 8016.59118) (10128.20419 8001.50837)))
("SF_SOLAR" 0 ((10128.20419 7971.34231) (10128.20419 7982.65452)))
("SF_SOLAR" 0 ((10128.20419 7971.34231) (10128.20419 7960.03020)))
("SF_SOLAR" 0 ((10128.20419 7937.40577) (10128.20419 7929.86425)))
("SF_MASONRY_AND_ARCH" 0 ((10128.20419 4924.58563) (10128.20419 4894.41889)))
("SF_MASONRY_AND_ARCH" 0 ((10245.09898 4890.64898) (10147.05882 4888.07545) (10128.20419 4894.41889)))
("SF_MASONRY_AND_ARCH" 0 ((10196.07749 2273.75566) (10188.53032 2270.13292) (10128.20419 2269.98518)))
("SF_MASONRY_AND_ARCH" 0 ((10128.20419 1689.29016) (10128.20419 1681.75057)))
("SF_MASONRY_AND_ARCH" 0 ((10128.20419 1681.75057) (10165.91346 1681.60215) (10180.99548 1674.20814)))
("SF_MASONRY_AND_ARCH" 0 ((10131.97681 3981.90045) (10316.73518 3989.59649) (10324.28450 3996.98382)))
("SF_MASONRY_AND_ARCH" 0 ((10131.97681 1726.99943) (10199.85011 1734.53903)))
("SF_MASONRY_AND_ARCH" 0 ((10139.51640 248.86878) (10128.35950 260.18100) (10131.97681 354.44853)))
("SF_MASONRY_AND_ARCH" 0 ((10131.97681 354.44853) (10169.68326 358.20735) (10188.53790 354.45543) (10339.36652
354.30147) (10354.44853 350.67873)))
("SF_ARCHITECTURE" 0 ((10135.74661 7688.53699) (10135.89434 7756.41029) (10140.71505 7771.48665) (10150.82862
7779.03473) (12051.28247 7779.03473) (12070.13575 7779.03473) (12085.21912 7779.03473) (12134.23790 7779.03473)
(12149.32127 7779.03473)))
("SF_ARCHITECTURE" 0 ((10139.51640 7635.74661) (10154.60124 7635.74661)))
("SF_MASONRY_AND_ARCH" 0 ((10139.51640 4215.68586) (10139.51640 4245.85260)))
("SF_MASONRY_AND_ARCH" 0 ((10165.91346 4249.62251) (10139.51640 4245.85260)))
("SF_MASONRY_AND_ARCH" 0 ((10139.51640 4215.68586) (10271.49321 4208.29943) (10285.37183 4219.45701) (10286.57523
4230.76923)))
("SF_MASONRY_AND_ARCH" 0 ((10147.05882 3925.33937) (10139.67172 3932.88733) (10139.51640 3951.73495)))
("SF_MASONRY_AND_ARCH" 0 ((10147.05882 3865.00713) (10139.51640 3883.86165)))
("SF_MASONRY_AND_ARCH" 0 ((10169.68326 3186.27455) (10143.28903 3186.27455)))
("SF_SOLAR" 0 ((10150.82862 7963.80090) (10147.05882 7982.65452)))
("SF_SOLAR" 0 ((10147.05882 7937.40577) (10147.05882 7922.32274)))
("SF_ARCHITECTURE" 0 ((10154.60124 7635.74661) (10154.45283 7616.89287) (10147.05882 7598.03925)))
("SF_MASONRY_AND_ARCH" 0 ((10147.05882 4724.73563) (10150.81618 4766.21459) (10147.05882 4785.06787)))
("SF_MASONRY_AND_ARCH" 0 ((10154.60124 4796.38009) (10147.05882 4785.06787)))
("SF_MASONRY_AND_ARCH" 0 ((10388.38518 4724.73563) (10343.13631 4720.96572) (10301.66007 4724.72941) (10147.05882
4724.73563)))
("SF_MASONRY_AND_ARCH" 0 ((10147.05882 3865.00713) (10196.07749 3865.00713)))
("SF_MASONRY_AND_ARCH" 0 ((10177.22568 131.97681) (10169.67636 118.24525) (10147.05882 120.66459)))
("SF_SOLAR" 0 ((10154.60124 8118.40113) (10150.82862 8133.48416)))
("SF_SOLAR" 0 ((10150.82862 8073.15226) (10150.82862 8088.23529)))
("SF_SOLAR" 0 ((10150.82862 8050.52783) (10150.82862 8039.21561)))
("SF_SOLAR" 0 ((10150.82862 8005.27896) (10150.82862 8016.59118)))
("SF_MASONRY_AND_ARCH" 0 ((10177.22568 5211.16097) (10150.82862 5211.16097)))
("SF_MASONRY_AND_ARCH" 0 ((10150.82862 4841.62896) (10158.37104 4856.71233)))
("SF_MASONRY_AND_ARCH" 0 ((10154.60124 4796.38009) (10150.82862 4819.00452)))
("SF_MASONRY_AND_ARCH" 0 ((10237.55656 3061.84038) (10150.82862 3061.84038)))
("SF_MASONRY_AND_ARCH" 0 ((10150.82862 2522.62443) (10150.82862 2564.10283)))
("SF_MASONRY_AND_ARCH" 0 ((10154.60124 2575.41505) (10150.82862 2564.10283)))
("SF_MASONRY_AND_ARCH" 0 ((10150.82862 2522.62443) (10188.53790 2515.08269)))
("SF_MASONRY_AND_ARCH" 0 ((10392.15781 1278.28054) (10339.36652 1259.72285) (10324.28450 1263.19163) (10162.14084
1263.35181) (10150.98394 1274.51075) (10150.82862 1338.61143)))
("SF_MASONRY_AND_ARCH" 0 ((10165.91346 1342.38405) (10150.82862 1338.61143)))
("SF_MASONRY_AND_ARCH" 0 ((10154.60124 1191.55260) (10150.82862 1233.03167)))
("SF_MASONRY_AND_ARCH" 0 ((10316.74208 177.22568) (10150.82862 177.22568)))
("SF_ARCHITECTURE" 0 ((10320.51278 7635.74661) (10154.60124 7635.74661)))
("SF_MASONRY_AND_ARCH" 0 ((10154.60124 4796.38009) (10162.14084 4796.38009)))
("SF_MASONRY_AND_ARCH" 0 ((10154.60124 1191.55260) (10218.70192 1184.16629) (10233.78676 1187.63507) (10286.57523
1187.78281)))
("SF_MASONRY_AND_ARCH" 0 ((10158.37104 5946.45543) (10237.54966 5946.30724) (10245.09898 5942.68484)))
("SF_MASONRY_AND_ARCH" 0 ((10388.38518 5848.41629) (10377.07296 5844.65204) (10245.09898 5847.21867) (10184.76527
5843.58903) (10173.60837 5836.95600) (10166.96222 5822.02104) (10165.75814 5776.77251) (10158.37104 5765.45995)))
("SF_MASONRY_AND_ARCH" 0 ((10158.37104 4404.22364) (10165.91833 4407.69762) (10177.22568 4404.37149) (10237.55656
4404.07523) (10248.86878 4400.45249)))
("SF_MASONRY_AND_ARCH" 0 ((10158.37104 3009.04977) (10196.07749 3009.04977)))
("SF_MASONRY_AND_ARCH" 0 ((10162.14084 5644.79638) (10207.38971 5641.02557)))
("SF_MASONRY_AND_ARCH" 0 ((10343.13631 5727.75271) (10328.05430 5723.98846) (10166.96912 5723.60667) (10162.28925
5712.67274) (10162.14084 5644.79638)))
("SF_MASONRY_AND_ARCH" 0 ((10162.14084 5339.36652) (10177.21810 5338.16889) (10184.76527 5331.82545)))
("SF_MASONRY_AND_ARCH" 0 ((10162.14084 5305.42986) (10162.28925 5263.95215) (10165.91346 5252.63993)))
("SF_MASONRY_AND_ARCH" 0 ((10162.14084 3404.97738) (10169.68326 3408.74785)))
("SF_MASONRY_AND_ARCH" 0 ((10162.14084 3288.08473) (10177.22568 3276.92715) (10294.11765 3280.54299) (10312.97229
3276.77251)))
("SF_MASONRY_AND_ARCH" 0 ((10196.07749 2865.76165) (10188.53032 2865.76165) (10162.14084 2865.76165)))
("SF_MASONRY_AND_ARCH" 0 ((10162.14084 987.93269) (10169.68326 984.16290)))
("SF_MASONRY_AND_ARCH" 0 ((10162.14084 889.89536) (10162.14084 923.83201)))
("SF_MASONRY_AND_ARCH" 0 ((10211.16233 859.72851) (10162.14084 852.18609)))
("SF_MASONRY_AND_ARCH" 0 ((10165.91346 690.04525) (10162.14084 618.40215)))
("SF_MASONRY_AND_ARCH" 0 ((10388.38518 5256.40984) (10256.41120 5252.64615) (10192.30769 5256.40362) (10165.91346
5252.63993)))
("SF_MASONRY_AND_ARCH" 0 ((10169.68326 3186.27455) (10165.91346 3197.58699)))
("SF_MASONRY_AND_ARCH" 0 ((10165.91346 946.45645) (10173.46063 953.69434) (10188.53790 950.38088) (10211.16233
953.84898) (10222.47455 950.22624)))
("SF_MASONRY_AND_ARCH" 0 ((10165.91346 565.61086) (10165.91346 539.21663)))
("SF_MASONRY_AND_ARCH" 0 ((10165.91346 539.21663) (10222.47455 539.06821) (10241.32636 532.87217) (10267.72342
539.06821) (10324.28450 539.21663)))
("SF_MASONRY_AND_ARCH" 0 ((10173.45305 3363.49898) (10173.30600 3397.43563) (10169.68326 3408.74785)))
("SF_MASONRY_AND_ARCH" 0 ((10173.45305 3469.08020) (10169.68326 3408.74785)))
("SF_MASONRY_AND_ARCH" 0 ((10169.68326 3186.27455) (10245.09140 3186.27455) (10252.63857 3186.27455)))
("SF_MASONRY_AND_ARCH" 0 ((10169.68326 984.16290) (10169.68326 976.62048)))
("SF_MASONRY_AND_ARCH" 0 ((10184.76527 1006.78733) (10169.68326 984.16290)))
("SF_SOLAR" 0 ((10175.33937 7993.96686) (10173.45305 7956.25939)))
("SF_SOLAR" 0 ((10177.22568 7926.09355) (10173.45305 7941.17647)))
("SF_MASONRY_AND_ARCH" 0 ((10173.45305 3469.08020) (10241.32636 3472.85068)))
("SF_MASONRY_AND_ARCH" 0 ((10173.45305 1866.51584) (10199.85011 1862.74536)))
("SF_MASONRY_AND_ARCH" 0 ((10173.45305 1632.72907) (10173.45305 1640.27149)))
("SF_MASONRY_AND_ARCH" 0 ((10173.45305 1606.33484) (10176.92873 1598.49695) (10305.42986 1595.02885) (10339.36652
1598.78756) (10354.44853 1595.02262)))
("SF_SOLAR" 0 ((10175.33937 7993.96686) (10199.85011 7993.96686)))
("SF_SOLAR" 0 ((10175.33937 7993.96686) (10180.69932 8020.35532) (10177.22568 8027.90339)))
("SF_SOLAR" 0 ((10184.76527 8061.84016) (10177.22568 8027.90339)))
("SF_SOLAR" 0 ((10184.76527 8061.84016) (10218.70192 8061.84016)))
("SF_SOLAR" 0 ((10184.76527 8061.84016) (10188.53790 8099.54751)))
("SF_MASONRY_AND_ARCH" 0 ((10207.38971 5015.08337) (10184.76527 5015.08337)))
("SF_MASONRY_AND_ARCH" 0 ((10196.07749 3672.69943) (10184.76527 3672.69943)))
("SF_MASONRY_AND_ARCH" 0 ((10184.76527 1006.78733) (10199.85011 1003.01753)))
("SF_MASONRY_AND_ARCH" 0 ((10196.07749 1085.97285) (10184.92059 1074.65441) (10188.24095 1048.26640) (10184.76527
1006.78733)))
("SF_MASONRY_AND_ARCH" 0 ((10282.80543 248.86878) (10184.76527 248.86878)))
("SF_MASONRY_AND_ARCH" 0 ((10186.65158 2405.73156) (10377.07296 2405.73156) (10388.38518 2405.73156)))
("SF_MASONRY_AND_ARCH" 0 ((10186.65158 2405.73156) (10188.68495 2349.17070) (10194.19400 2334.08722)))
("SF_MASONRY_AND_ARCH" 0 ((10188.53790 2515.08269) (10184.77285 2500.00000) (10188.53100 2477.37557) (10184.77217
2450.98066) (10186.65158 2405.73156)))
("SF_SOLAR" 0 ((10188.53790 8099.54751) (10196.07749 8118.40113)))
("SF_SOLAR" 0 ((10188.53790 8027.90339) (10211.16233 8024.13281)))
("SF_MASONRY_AND_ARCH" 0 ((10196.07749 5395.92760) (10188.53790 5392.15645)))
("SF_MASONRY_AND_ARCH" 0 ((10188.53790 2515.08269) (10211.16233 2518.84774) (10361.99095 2518.85396)))
("SF_SOLAR" 0 ((10192.30769 7850.67873) (10192.30769 7858.22025)))
("SF_MASONRY_AND_ARCH" 0 ((10192.30769 6025.64095) (10207.38971 6025.64095)))
("SF_MASONRY_AND_ARCH" 0 ((10196.07749 6093.51425) (10192.30769 6025.64095)))
("SF_MASONRY_AND_ARCH" 0 ((10192.30769 5493.96640) (10188.55034 5478.88428) (10194.88032 5452.48869) (10192.30769
5441.17647)))
("SF_MASONRY_AND_ARCH" 0 ((10388.38518 5441.17647) (10354.44853 5437.40532) (10286.57523 5441.17647) (10207.38971
5437.41222) (10192.30769 5441.17647)))
("SF_MASONRY_AND_ARCH" 0 ((10192.30769 4249.62251) (10230.01414 4253.39367)))
("SF_MASONRY_AND_ARCH" 0 ((10377.07296 1338.61143) (10369.52579 1342.23563) (10290.34785 1344.95588) (10248.86878
1342.38891) (10214.93213 1346.14762) (10192.30769 1342.38405)))
("SF_SOLAR" 0 ((10194.19400 8141.02568) (10222.46697 8141.02568) (10230.01414 8141.02568)))
("SF_SOLAR" 0 ((10194.19400 8141.02568) (10192.46233 8125.94932) (10196.07749 8118.40113)))
("SF_SOLAR" 0 ((10203.61991 8171.19163) (10197.27613 8167.26618) (10194.19400 8141.02568)))
("SF_MASONRY_AND_ARCH" 0 ((10194.19400 2334.08722) (10196.07749 2273.75566)))
("SF_MASONRY_AND_ARCH" 0 ((10392.15781 2334.08722) (10331.82410 2332.41572) (10275.26301 2337.85848) (10214.93213
2337.71075) (10194.19400 2334.08722)))
("SF_SOLAR" 0 ((10207.38971 8114.63054) (10196.07749 8118.40113)))
("SF_MASONRY_AND_ARCH" 0 ((10373.30317 6097.28507) (10361.99095 6099.85803) (10339.36652 6093.52081) (10196.07749
6093.51425)))
("SF_MASONRY_AND_ARCH" 0 ((10196.07749 3865.00713) (10203.62681 3853.69536) (10226.24434 3852.02398) (10252.63857
3854.89966) (10263.95079 3868.77828)))
("SF_MASONRY_AND_ARCH" 0 ((10196.07749 3865.00713) (10211.16233 3876.16538) (10248.86878 3876.17149) (10263.95079
3868.77828)))
("SF_MASONRY_AND_ARCH" 0 ((10290.34785 2262.44344) (10275.26301 2269.83665) (10203.62681 2270.13292) (10196.07749
2273.75566)))
("SF_MASONRY_AND_ARCH" 0 ((10196.07749 1794.87274) (10211.16233 1806.02964) (10377.07296 1802.41233) (10395.92760
1806.18495)))
("SF_MASONRY_AND_ARCH" 0 ((10196.07749 1760.93609) (10199.85011 1734.53903)))
("SF_SOLAR" 0 ((10211.16233 8099.54751) (10199.85011 8099.54751)))
("SF_MASONRY_AND_ARCH" 0 ((10199.85011 2088.98971) (10203.77455 2095.48122) (10226.24434 2104.07240)))
("SF_MASONRY_AND_ARCH" 0 ((10199.85011 1855.20362) (10199.85011 1862.74536)))
("SF_MASONRY_AND_ARCH" 0 ((10309.19966 1870.28631) (10260.18100 1862.89310) (10199.85011 1862.74536)))
("SF_MASONRY_AND_ARCH" 0 ((10199.85011 1734.53903) (10230.01414 1730.76923)))
("SF_MASONRY_AND_ARCH" 0 ((10271.49321 6206.63654) (10263.94593 6206.63654) (10211.16719 6206.63654) (10203.61991
6206.63654)))
("SF_MASONRY_AND_ARCH" 0 ((10203.61991 6157.61697) (10199.85011 6172.69977) (10199.99717 6195.31765) (10203.61991
6206.63654)))
("SF_SOLAR" 0 ((10207.38971 8197.58665) (10207.38971 8182.50385)))
("SF_SOLAR" 0 ((10207.38971 7922.32274) (10211.16233 7948.71799)))
("SF_SOLAR" 0 ((10211.16233 7993.96686) (10211.16233 8024.13281)))
("SF_SOLAR" 0 ((10218.70192 8027.90339) (10211.16233 8024.13281)))
("SF_SOLAR" 0 ((10346.90894 7993.96686) (10211.16233 7993.96686)))
("SF_SOLAR" 0 ((10211.16233 7993.96686) (10207.38971 7975.11312) (10211.16233 7948.71799)))
("SF_SOLAR" 0 ((10339.36652 7948.71799) (10211.16233 7948.71799)))
("SF_MASONRY_AND_ARCH" 0 ((10230.01414 3714.17839) (10211.16233 3706.63609)))
("SF_MASONRY_AND_ARCH" 0 ((10218.70192 2130.46731) (10211.16233 2119.15509)))
("SF_SOLAR" 0 ((10230.01414 8163.65000) (10222.47455 8171.19163) (10214.93213 8171.19163)))
("SF_SOLAR" 0 ((10218.70192 8061.84016) (10377.07296 8061.84016)))
("SF_SOLAR" 0 ((10218.70192 8061.84016) (10218.70192 8054.29864) (10218.70192 8027.90339)))
("SF_SOLAR" 0 ((10222.47455 8133.48416) (10218.99887 8118.40113) (10222.46765 8095.77670) (10218.70192 8061.84016)))
("SF_SOLAR" 0 ((10365.76075 8031.67421) (10350.67873 8027.90995) (10218.70192 8027.90339)))
("SF_MASONRY_AND_ARCH" 0 ((10218.70192 3333.33360) (10305.42986 3329.71007) (10316.74208 3333.18586) (10335.58914
3331.81663) (10343.13631 3340.87455)))
("SF_MASONRY_AND_ARCH" 0 ((10218.70192 2865.76165) (10290.34785 2865.76165) (10320.50701 2865.76165) (10331.82410
2880.84491)))
("SF_MASONRY_AND_ARCH" 0 ((10339.36652 1674.20814) (10218.70192 1674.20814)))
("SF_MASONRY_AND_ARCH" 0 ((10226.24434 3759.42726) (10222.47455 3766.96833)))
("SF_MASONRY_AND_ARCH" 0 ((10222.47455 3005.27930) (10236.35170 3001.35339) (10241.32636 2944.94695)))
("SF_MASONRY_AND_ARCH" 0 ((10226.24434 5641.02557) (10237.55656 5633.48416)))
("SF_SOLAR" 0 ((10230.01414 8163.65000) (10230.01414 8141.02568)))
("SF_SOLAR" 0 ((10230.01414 8163.65000) (10305.42986 8163.79808) (10320.51188 8167.40769) (10335.59672 8163.79808)
(10377.07296 8163.65000)))
("SF_SOLAR" 0 ((10388.38518 8141.02568) (10380.84559 8141.02568) (10245.09898 8141.02568) (10230.01414 8141.02568)))
("SF_MASONRY_AND_ARCH" 0 ((10230.01414 3800.90498) (10233.78676 3797.13382) (10245.09898 3797.13382)))
("SF_MASONRY_AND_ARCH" 0 ((10245.09898 3672.69943) (10230.01414 3676.47059)))
("SF_SOLAR" 0 ((10233.78676 8099.54751) (10275.26301 8103.31176) (10369.53337 8103.31833)))
("SF_MASONRY_AND_ARCH" 0 ((10335.59672 1093.51527) (10279.03563 1086.12059) (10233.78676 1085.97285)))
("SF_MASONRY_AND_ARCH" 0 ((10392.15781 1003.01753) (10233.78676 1003.01753)))
("SF_MASONRY_AND_ARCH" 0 ((10237.55656 5633.48416) (10237.55656 5607.08857)))
("SF_MASONRY_AND_ARCH" 0 ((10237.55656 5633.48416) (10252.63857 5643.59186) (10279.03563 5641.03213) (10294.11765
5644.64830) (10358.22115 5644.78982) (10380.84559 5641.03213) (10392.15781 5644.79638)))
("SF_MASONRY_AND_ARCH" 0 ((10237.55656 5607.08857) (10241.32636 5550.52749)))
("SF_MASONRY_AND_ARCH" 0 ((10237.55656 5222.47319) (10256.41120 5222.47319)))
("SF_MASONRY_AND_ARCH" 0 ((10237.55656 3631.22172) (10263.95079 3631.06708) (10275.26301 3623.68066)))
("SF_MASONRY_AND_ARCH" 0 ((10237.55656 3061.84038) (10242.53122 3039.37059) (10248.87568 3035.59932) (10392.15781
3035.44468)))
("SF_MASONRY_AND_ARCH" 0 ((10237.55656 3061.84038) (10242.52500 3088.22907) (10256.41120 3098.49118) (10388.38518
3099.54751)))
("SF_SOLAR" 0 ((10241.32636 8016.59118) (10241.32636 8001.50837)))
("SF_SOLAR" 0 ((10241.32636 7982.65452) (10244.41753 7971.71086) (10263.95079 7971.34231)))
("SF_SOLAR" 0 ((10241.32636 7941.17647) (10241.32636 7922.32274)))
("SF_MASONRY_AND_ARCH" 0 ((10241.32636 6025.64095) (10365.76075 6025.49276) (10383.26210 6017.94491) (10380.99887
6003.02308) (10384.61538 5995.47511)))
("SF_MASONRY_AND_ARCH" 0 ((10331.82410 5542.98643) (10275.26301 5543.13450) (10241.32636 5550.52749)))
("SF_MASONRY_AND_ARCH" 0 ((10241.32636 5011.31222) (10248.86878 5007.54106)))
("SF_MASONRY_AND_ARCH" 0 ((10241.32636 4920.81448) (10245.09898 4890.64898)))
("SF_MASONRY_AND_ARCH" 0 ((10241.32636 4690.79898) (10241.32636 4668.17455)))
("SF_MASONRY_AND_ARCH" 0 ((10392.15781 4630.46799) (10377.07296 4634.23167) (10241.32636 4634.23790)))
("SF_MASONRY_AND_ARCH" 0 ((10241.32636 4634.23790) (10241.32636 4615.38462)))
("SF_MASONRY_AND_ARCH" 0 ((10241.32636 3503.01686) (10241.32636 3472.85068)))
("SF_MASONRY_AND_ARCH" 0 ((10263.95079 3506.78733) (10241.32636 3503.01686)))
("SF_MASONRY_AND_ARCH" 0 ((10388.38518 3472.85068) (10241.32636 3472.85068)))
("SF_MASONRY_AND_ARCH" 0 ((10392.15781 2937.40600) (10373.30317 2941.17647) (10297.88744 2937.55441) (10241.32636
2944.94695)))
("SF_MASONRY_AND_ARCH" 0 ((10248.86878 2771.49321) (10248.72104 2745.09830) (10241.32636 2726.24434)))
("SF_MASONRY_AND_ARCH" 0 ((10241.32636 1730.76923) (10320.51188 1730.76301) (10346.90894 1727.14717) (10369.53337
1737.25452) (10392.15781 1738.31165)))
("SF_MASONRY_AND_ARCH" 0 ((10388.38518 426.09446) (10271.49321 426.08756) (10248.87568 422.47715) (10242.53122
426.24774) (10241.32636 441.17647)))
("SF_MASONRY_AND_ARCH" 0 ((10316.74208 79.18552) (10301.66007 75.56278) (10241.32636 75.41572)))
("SF_MASONRY_AND_ARCH" 0 ((10256.41120 5908.74819) (10246.15464 5923.83100) (10245.09898 5942.68484)))
("SF_MASONRY_AND_ARCH" 0 ((10245.09898 5942.68484) (10256.41120 5946.30724) (10354.44853 5950.22624)))
("SF_MASONRY_AND_ARCH" 0 ((10245.09898 4890.64898) (10365.76075 4890.64208) (10380.83801 4887.17432) (10388.38518
4890.64898)))
("SF_MASONRY_AND_ARCH" 0 ((10245.09898 4377.82805) (10248.86878 4400.45249)))
("SF_MASONRY_AND_ARCH" 0 ((10286.57523 950.22624) (10252.64615 950.37398) (10245.09898 953.99604)))
("SF_MASONRY_AND_ARCH" 0 ((10245.09898 855.95871) (10260.18100 855.95871)))
("SF_MASONRY_AND_ARCH" 0 ((10248.86878 4973.60441) (10248.86878 5007.54106)))
("SF_MASONRY_AND_ARCH" 0 ((10279.03563 5011.31222) (10248.86878 5007.54106)))
("SF_MASONRY_AND_ARCH" 0 ((10248.86878 4973.60441) (10388.38518 4973.60441)))
("SF_MASONRY_AND_ARCH" 0 ((10358.22115 4404.22364) (10279.03563 4404.21674) (10248.86878 4400.45249)))
("SF_MASONRY_AND_ARCH" 0 ((10248.86878 3152.33812) (10252.49152 3159.88597) (10252.63857 3186.27455)))
("SF_MASONRY_AND_ARCH" 0 ((10248.86878 2771.49321) (10260.18100 2775.11595) (10324.28450 2775.41143) (10339.36652
2779.02183) (10388.38518 2775.26369)))
("SF_MASONRY_AND_ARCH" 0 ((10248.86878 2688.53722) (10263.95079 2695.92975) (10388.38518 2696.07817)))
("SF_MASONRY_AND_ARCH" 0 ((10388.38518 3186.27455) (10267.72342 3186.27455) (10252.63857 3186.27455)))
("SF_MASONRY_AND_ARCH" 0 ((10252.63857 2654.60057) (10252.63857 2628.20486)))
("SF_MASONRY_AND_ARCH" 0 ((10252.63857 2628.20486) (10279.03563 2624.44061) (10316.74208 2628.19864) (10354.22896
2624.94389) (10358.22115 2631.97613)))
("SF_MASONRY_AND_ARCH" 0 ((10260.18100 904.97738) (10252.63857 904.97738)))
("SF_MASONRY_AND_ARCH" 0 ((10252.63857 818.24943) (10267.72342 810.71606) (10365.76075 814.47964)))
("SF_SOLAR" 0 ((10260.18100 8069.38167) (10260.18100 8084.46448)))
("SF_SOLAR" 0 ((10263.95079 8122.17195) (10263.95079 8133.48416)))
("SF_SOLAR" 0 ((10263.95079 8050.52783) (10263.95079 8035.44502)))
("SF_SOLAR" 0 ((10263.95079 8001.50837) (10263.95079 8016.59118)))
("SF_SOLAR" 0 ((10263.95079 7971.34231) (10263.95079 7982.65452)))
("SF_SOLAR" 0 ((10290.34785 7971.34231) (10263.95079 7971.34231)))
("SF_SOLAR" 0 ((10263.95079 7941.17647) (10263.95079 7926.09355)))
("SF_MASONRY_AND_ARCH" 0 ((10267.72342 6297.13416) (10263.95079 6308.44638)))
("SF_MASONRY_AND_ARCH" 0 ((10286.57523 6319.75860) (10275.26301 6318.55441) (10263.95079 6308.44638)))
("SF_MASONRY_AND_ARCH" 0 ((10384.61538 3868.77828) (10358.22115 3872.54943) (10263.95079 3868.77828)))
("SF_MASONRY_AND_ARCH" 0 ((10267.72342 6297.13416) (10264.09921 6244.34389) (10271.49321 6206.63654)))
("SF_MASONRY_AND_ARCH" 0 ((10267.72342 6297.13416) (10290.34785 6304.67579)))
("SF_MASONRY_AND_ARCH" 0 ((10388.38518 6206.63654) (10373.30317 6206.63654) (10282.80543 6206.63654) (10271.49321
6206.63654)))
("SF_MASONRY_AND_ARCH" 0 ((10275.26301 3623.68066) (10271.49321 3593.51459)))
("SF_MASONRY_AND_ARCH" 0 ((10328.05430 3680.24174) (10320.50701 3676.61867) (10275.26301 3676.47059)))
("SF_MASONRY_AND_ARCH" 0 ((10392.15781 3631.22172) (10354.44853 3623.82851) (10316.74208 3627.44434) (10275.26301
3623.68066)))
("SF_MASONRY_AND_ARCH" 0 ((10275.26301 3570.89016) (10350.67183 3571.04480) (10357.01629 3574.80837) (10358.22115
3582.20238)))
("SF_MASONRY_AND_ARCH" 0 ((10275.26301 3529.41176) (10282.81233 3525.78903) (10354.44853 3525.64129)))
("SF_MASONRY_AND_ARCH" 0 ((10279.03563 4170.43699) (10282.80543 4144.04265)))
("SF_MASONRY_AND_ARCH" 0 ((10369.53337 3789.59276) (10279.03563 3793.36391)))
("SF_MASONRY_AND_ARCH" 0 ((10282.80543 4144.04265) (10305.42986 4140.28462) (10343.13631 4147.66471) (10388.38518
4147.81256)))
("SF_SOLAR" 0 ((10286.57523 8133.48416) (10286.57523 8118.40113)))
("SF_SOLAR" 0 ((10286.57523 8073.15226) (10286.57523 8088.23529)))
("SF_SOLAR" 0 ((10286.57523 8050.52783) (10286.57523 8035.44502)))
("SF_SOLAR" 0 ((10286.57523 8016.59118) (10286.57523 8001.50837)))
("SF_SOLAR" 0 ((10290.34785 7971.34231) (10286.57523 7982.65452)))
("SF_SOLAR" 0 ((10286.57523 7926.09355) (10290.34785 7941.17647)))
("SF_MASONRY_AND_ARCH" 0 ((10388.38518 6391.40271) (10286.57523 6391.40271)))
("SF_MASONRY_AND_ARCH" 0 ((10286.57523 6361.23688) (10286.57523 6391.40271)))
("SF_MASONRY_AND_ARCH" 0 ((10286.57523 6319.75860) (10290.34785 6304.67579)))
("SF_MASONRY_AND_ARCH" 0 ((10286.57523 6319.75860) (10290.34785 6327.30023)))
("SF_MASONRY_AND_ARCH" 0 ((10286.57523 4253.39367) (10358.22115 4253.39367)))
("SF_MASONRY_AND_ARCH" 0 ((10286.57523 2243.58948) (10290.34785 2262.44344)))
("SF_MASONRY_AND_ARCH" 0 ((10380.84559 1180.24038) (10361.99095 1183.86459) (10294.12455 1184.16007) (10286.57523
1187.78281)))
("SF_MASONRY_AND_ARCH" 0 ((10350.67873 1229.26188) (10343.13145 1219.14683) (10294.12455 1209.20928) (10287.78009
1202.85995) (10286.57523 1187.78281)))
("SF_SOLAR" 0 ((10290.34785 7971.34231) (10301.66007 7971.34231) (10305.42986 7967.57172)))
("SF_MASONRY_AND_ARCH" 0 ((10388.38518 6304.67579) (10369.53337 6300.90498) (10309.19966 6301.05305) (10290.34785
6304.67579)))
("SF_MASONRY_AND_ARCH" 0 ((10290.34785 2262.44344) (10324.28450 2269.83744) (10388.38518 2269.98518)))
("SF_MASONRY_AND_ARCH" 0 ((10388.38518 4600.30124) (10377.07296 4596.53756) (10358.22115 4600.15339) (10320.51188
4599.24514) (10306.33778 4585.21844) (10301.66007 4562.59468)))
("SF_SOLAR" 0 ((10305.42986 7941.17647) (10309.19966 7926.09355)))
("SF_MASONRY_AND_ARCH" 0 ((10320.51188 5041.47771) (10319.30848 5022.63066) (10305.42986 5015.08337)))
("SF_SOLAR" 0 ((10309.19966 8118.40113) (10309.19966 8133.48416)))
("SF_SOLAR" 0 ((10309.19966 8073.15226) (10309.19966 8084.46448)))
("SF_SOLAR" 0 ((10312.97229 8039.21561) (10309.19966 8046.75724)))
("SF_SOLAR" 0 ((10309.19966 8005.27896) (10309.19966 8016.59118)))
("SF_MASONRY_AND_ARCH" 0 ((10309.19966 1957.01357) (10316.89672 1985.97557) (10392.15781 1983.40848)))
("SF_MASONRY_AND_ARCH" 0 ((10309.19966 1870.28631) (10309.19966 1915.53518)))
("SF_MASONRY_AND_ARCH" 0 ((10309.19966 1870.28631) (10392.15781 1862.74536)))
("SF_MASONRY_AND_ARCH" 0 ((10388.38518 950.22624) (10373.30317 953.99604) (10309.19966 950.22624)))
("SF_MASONRY_AND_ARCH" 0 ((10395.92760 855.95871) (10373.30317 852.33450) (10309.19966 852.18609)))
("SF_MASONRY_AND_ARCH" 0 ((10316.74208 5064.10215) (10320.51188 5086.72658)))
("SF_MASONRY_AND_ARCH" 0 ((10316.74208 79.18552) (10312.97229 124.43439) (10316.74208 177.22568)))
("SF_MASONRY_AND_ARCH" 0 ((10392.15781 184.76527) (10316.74208 177.22568)))
("SF_MASONRY_AND_ARCH" 0 ((10316.74208 79.18552) (10328.05430 75.56278) (10384.61538 75.41572)))
("SF_SOLAR" 0 ((10328.05430 8197.58665) (10320.51188 8178.73303)))
("SF_ARCHITECTURE" 0 ((10369.53337 6828.80848) (10328.06120 6828.80848) (10320.51188 6828.80848)))
("SF_ARCHITECTURE" 0 ((10320.51188 6828.80848) (10320.51278 6881.59853) (10320.51278 6923.07692) (10320.51278
7556.56109) (10320.51278 7571.64400)))
("SF_MASONRY_AND_ARCH" 0 ((10384.61538 4072.39819) (10328.06120 4072.54627) (10320.51188 4076.16934)))
("SF_MASONRY_AND_ARCH" 0 ((10320.51188 614.62952) (10324.28450 592.00509)))
("SF_ARCHITECTURE" 0 ((10320.51278 7635.74661) (10320.51278 7620.66369) (10320.51278 7582.95633) (10320.51278
7571.64400)))
("SF_ARCHITECTURE" 0 ((10320.51278 7635.74661) (10324.43778 7650.67489) (10331.82410 7654.44570) (10418.55204
7654.74842) (10433.63405 7658.36448) (10603.31731 7658.36448) (10622.17195 7654.60690) (10799.39762 7658.37104)
(10822.02206 7654.60690) (11070.89084 7654.59378) (11082.04774 7650.67500) (11089.74355 7639.51731)))
("SF_MASONRY_AND_ARCH" 0 ((10324.28450 3996.98382) (10392.15781 3989.44152)))
("SF_MASONRY_AND_ARCH" 0 ((10324.28450 671.19061) (10320.51188 674.96324) (10324.28450 678.73303)))
("SF_MASONRY_AND_ARCH" 0 ((10324.28450 565.61086) (10320.66719 554.29864) (10324.28450 539.21663)))
("SF_MASONRY_AND_ARCH" 0 ((10388.38518 535.44400) (10331.83167 535.59242) (10324.28450 539.21663)))
("SF_SOLAR" 0 ((10331.82410 8046.75724) (10328.05430 8039.21561)))
("SF_MASONRY_AND_ARCH" 0 ((10358.22115 4483.40916) (10328.05430 4483.40916)))
("SF_MASONRY_AND_ARCH" 0 ((10328.05430 2907.23982) (10328.05430 2895.92760) (10331.82410 2892.15713)))
("SF_MASONRY_AND_ARCH" 0 ((10331.82410 2021.11640) (10328.05430 2047.51131)))
("SF_MASONRY_AND_ARCH" 0 ((10328.05430 2047.51131) (10331.82410 2055.05305)))
("SF_SOLAR" 0 ((10331.82410 8073.15226) (10331.82410 8084.46448)))
("SF_SOLAR" 0 ((10331.82410 8016.59118) (10331.82410 8001.50837)))
("SF_MASONRY_AND_ARCH" 0 ((10350.67873 2055.05305) (10331.82410 2055.05305)))
("SF_MASONRY_AND_ARCH" 0 ((10331.82410 2055.05305) (10328.20204 2096.53066) (10331.97251 2134.23857) (10336.65238
2145.39615) (10343.14389 2149.16663) (10388.38518 2149.32127)))
("SF_MASONRY_AND_ARCH" 0 ((10343.13631 5403.46867) (10335.59672 5403.46867)))
("SF_MASONRY_AND_ARCH" 0 ((10335.59672 2835.59604) (10331.82410 2831.82477) (10335.59672 2824.28382)))
("SF_SOLAR" 0 ((10339.36652 7948.71799) (10343.13631 7929.86425)))
("SF_SOLAR" 0 ((10361.99095 8020.36199) (10353.39977 7982.65452) (10339.36652 7948.71799)))
("SF_MASONRY_AND_ARCH" 0 ((10339.36652 3291.85520) (10337.84966 3284.31346) (10343.15011 3277.97658) (10361.99095
3273.14898) (10388.38518 3273.00124)))
("SF_MASONRY_AND_ARCH" 0 ((10343.13631 5727.75271) (10354.44853 5725.17952) (10392.15781 5731.52330)))
("SF_MASONRY_AND_ARCH" 0 ((10346.90894 5746.60633) (10343.13631 5727.75271)))
("SF_MASONRY_AND_ARCH" 0 ((10354.44853 1595.02262) (10349.48156 1568.63326) (10343.13631 1561.08597)))
("SF_MASONRY_AND_ARCH" 0 ((10343.13631 1478.13066) (10343.13631 1440.42138)))
("SF_MASONRY_AND_ARCH" 0 ((10388.38518 1440.42138) (10343.13631 1440.42138)))
("SF_MASONRY_AND_ARCH" 0 ((10343.13631 245.09898) (10354.59695 260.18100) (10350.68563 275.26301) (10354.44853
350.67873)))
("SF_SOLAR" 0 ((10535.44400 7948.71799) (10350.67873 7948.71799)))
("SF_MASONRY_AND_ARCH" 0 ((10392.15781 4517.34581) (10384.60848 4513.72274) (10350.67873 4513.57466)))
("SF_SOLAR" 0 ((10354.44853 8118.40113) (10354.44853 8133.48416)))
("SF_MASONRY_AND_ARCH" 0 ((10354.44853 5139.51776) (10354.44853 5124.43439)))
("SF_MASONRY_AND_ARCH" 0 ((10392.15781 5120.66324) (10354.44853 5124.43439)))
("SF_MASONRY_AND_ARCH" 0 ((10354.44853 3676.47059) (10380.84559 3672.69943)))
("SF_MASONRY_AND_ARCH" 0 ((10395.92760 1595.02262) (10354.44853 1595.02262)))
("SF_MASONRY_AND_ARCH" 0 ((10388.38518 354.44853) (10354.44853 350.67873)))
("SF_MASONRY_AND_ARCH" 0 ((10388.38518 5192.30769) (10365.76833 5192.15962) (10358.22115 5188.53654)))
("SF_MASONRY_AND_ARCH" 0 ((10358.22115 4404.22364) (10358.22115 4434.38914)))
("SF_MASONRY_AND_ARCH" 0 ((10358.22115 4404.22364) (10384.61538 4400.45249)))
("SF_MASONRY_AND_ARCH" 0 ((10377.07296 1097.28507) (10358.22115 1093.51527)))
("SF_SOLAR" 0 ((10373.30317 7971.34231) (10361.99095 7971.34231)))
("SF_MASONRY_AND_ARCH" 0 ((10392.15781 2515.08269) (10361.99095 2518.85396)))
("SF_MASONRY_AND_ARCH" 0 ((10365.76075 2575.41505) (10362.13869 2567.86640) (10361.99095 2518.85396)))
("SF_SOLAR" 0 ((10365.76075 8031.67421) (10377.07296 8027.90995) (10558.06844 8027.90339)))
("SF_SOLAR" 0 ((10365.76075 8031.67421) (10369.53337 8054.29864)))
("SF_SOLAR" 0 ((10365.76075 7993.96686) (10384.61538 7993.96686)))
("SF_MASONRY_AND_ARCH" 0 ((10377.07296 5539.21527) (10365.76075 5542.98643)))
("SF_SOLAR" 0 ((10373.30317 7941.17647) (10369.53337 7929.86425)))
("SF_ARCHITECTURE" 0 ((10369.53337 6828.80848) (10452.48869 6828.80848) (10475.11312 6840.12093)))
("SF_ARCHITECTURE" 0 ((10369.53337 6828.80848) (10369.52647 7541.47817) (10365.76075 7582.95622) (10369.68665
7597.89118) (10388.38518 7605.58066) (11025.63439 7605.58066) (11033.18247 7590.49774) (11033.18247 6557.31550)))
("SF_MASONRY_AND_ARCH" 0 ((10384.61538 4803.92115) (10373.30317 4796.38009)))
("SF_MASONRY_AND_ARCH" 0 ((10392.15781 2058.82353) (10373.30317 2055.05305)))
("SF_SOLAR" 0 ((10377.07296 8061.84016) (10395.92760 8061.84016)))
("SF_SOLAR" 0 ((10388.38518 8141.02568) (10377.22138 8095.77670) (10377.07296 8076.92308) (10377.07296 8069.38167)
(10377.07296 8061.84016)))
("SF_MASONRY_AND_ARCH" 0 ((10392.15781 5942.68484) (10384.61538 5950.22624) (10377.07296 5946.45543)))
("SF_MASONRY_AND_ARCH" 0 ((10377.07296 5539.21527) (10380.84559 5512.82093)))
("SF_MASONRY_AND_ARCH" 0 ((10384.61538 5542.98643) (10377.07296 5539.21527)))
("SF_MASONRY_AND_ARCH" 0 ((10377.07296 5482.65419) (10384.76312 5492.76256) (10395.92760 5493.96640)))
("SF_MASONRY_AND_ARCH" 0 ((10377.07296 4864.25339) (10377.07296 4845.40011)))
("SF_MASONRY_AND_ARCH" 0 ((10377.07296 3929.11052) (10388.38518 3932.88043)))
("SF_MASONRY_AND_ARCH" 0 ((10377.07296 1338.61143) (10377.07296 1312.21719)))
("SF_MASONRY_AND_ARCH" 0 ((10377.07296 1338.61143) (10392.15781 1346.15385)))
("SF_MASONRY_AND_ARCH" 0 ((10377.07296 1097.28507) (10377.07296 1157.61595)))
("SF_MASONRY_AND_ARCH" 0 ((10392.15781 1093.51527) (10377.07296 1097.28507)))
("SF_SOLAR" 0 ((10380.84559 7956.25939) (10381.90124 7967.57172) (10395.92760 7993.96686)))
("SF_MASONRY_AND_ARCH" 0 ((10380.84559 814.47964) (10395.92760 814.47964)))
("SF_SOLAR" 0 ((10414.78224 8141.02568) (10388.38518 8141.02568)))
("SF_SOLAR" 0 ((10388.38518 8141.02568) (10388.54050 8159.87930) (10395.93450 8170.13529) (10411.00962 8173.89943)
(10424.88959 8163.64344) (10425.94604 8148.56719) (10414.92998 8114.63054) (10407.23982 8061.84016)))
("SF_MASONRY_AND_ARCH" 0 ((10395.92760 5920.06041) (10388.53360 5901.20656) (10388.38518 5874.81154)))
("SF_SOLAR" 0 ((10392.15781 8103.31833) (10403.47002 8099.54751)))
("SF_SOLAR" 0 ((10395.92760 7993.96686) (10392.17025 8005.27896) (10395.92760 8016.59118)))
("SF_SOLAR" 0 ((10546.75622 7993.96686) (10395.92760 7993.96686)))
("SF_MASONRY_AND_ARCH" 0 ((10395.92760 4766.21459) (10395.92760 4777.52681)))
("SF_SOLAR" 0 ((10399.69740 8182.50385) (10411.00962 8197.58665)))
("SF_SOLAR" 0 ((10399.69740 8039.21561) (10407.23982 8061.84016)))
("SF_SOLAR" 0 ((10407.23982 8061.84016) (10565.61086 8061.84016)))
("SF_SOLAR" 0 ((10418.55204 7967.57172) (10422.32183 7971.34231) (10422.32183 7982.65452)))
("SF_SOLAR" 0 ((10573.15328 8107.08891) (10554.29864 8099.84367) (10542.98643 8103.02217) (10531.67421 8099.84367)
(10516.59219 8103.31176) (10437.40667 8103.31176) (10422.32183 8099.54751)))
("SF_SOLAR" 0 ((10426.09446 8005.27896) (10426.09446 8016.59118)))
("SF_SOLAR" 0 ((10433.63405 8167.42081) (10448.71889 8163.65656) (10592.00509 8163.65000)))
("SF_SOLAR" 0 ((10433.63405 8141.02568) (10580.69287 8141.02568)))
("SF_SOLAR" 0 ((10444.94627 8069.38167) (10444.94627 8084.46448)))
("SF_SOLAR" 0 ((10444.94627 8039.21561) (10444.94627 8050.52783)))
("SF_SOLAR" 0 ((10444.94627 8005.27896) (10444.94627 8016.59118)))
("SF_SOLAR" 0 ((10444.94627 7982.65452) (10444.94627 7963.80090)))
("SF_ARCHITECTURE" 0 ((10448.71799 5750.37715) (12039.97025 5750.37704)))
("SF_MASONRY_AND_ARCH" 0 ((10448.71799 5607.08857) (10448.71799 5739.06459) (10448.71799 5750.37715)))
("SF_MASONRY_AND_ARCH" 0 ((10452.48869 5829.56267) (10448.71889 5814.47964) (10448.71799 5757.92511) (10448.71799
5750.37715)))
("SF_ARCHITECTURE" 0 ((12043.74061 5607.08857) (10448.71799 5607.08857)))
("SF_MASONRY_AND_ARCH" 0 ((10452.48869 2820.51278) (10448.72376 2831.82477) (10448.71199 3880.09050) (10444.94627
3902.71493) (10448.71799 4400.45249) (10448.71799 4423.07692) (10448.71799 4539.97025) (10448.71799 4562.59468)
(10448.71799 4641.78020) (10448.71799 4656.86233) (10448.71799 5554.29864) (10448.71799 5588.23529) (10448.71799
5607.08857)))
("SF_ARCHITECTURE" 0 ((10505.27998 6451.73462) (10460.03111 6451.73450) (10448.71889 6451.73450)))
("SF_MASONRY_AND_ARCH" 0 ((10448.71889 6195.32432) (10448.71889 6451.73450)))
("SF_ARCHITECTURE" 0 ((12006.03360 6195.32432) (10448.71889 6195.32432)))
("SF_MASONRY_AND_ARCH" 0 ((10452.48869 5829.56267) (10448.72376 5840.87489) (10448.71889 6195.32432)))
("SF_ARCHITECTURE" 0 ((12051.28201 2707.39038) (10448.71889 2707.39038)))
("SF_MASONRY_AND_ARCH" 0 ((10452.48869 2092.76018) (10448.72376 2104.07240) (10448.71199 2469.83382) (10444.95317
2488.68778) (10448.71199 2541.47839) (10448.71889 2707.39038)))
("SF_MASONRY_AND_ARCH" 0 ((10452.48869 2820.51278) (10448.72376 2809.20034) (10448.71889 2707.39038)))
("SF_ARCHITECTURE" 0 ((12058.82353 120.66369) (10448.71889 124.43439)))
("SF_MASONRY_AND_ARCH" 0 ((10448.71889 64.10351) (10448.71889 124.43439)))
("SF_MASONRY_AND_ARCH" 0 ((10448.71889 124.43439) (10448.86595 173.45305) (10452.48869 184.76527)))
("SF_MASONRY_AND_ARCH" 0 ((10448.71889 -3.77070) (10448.71889 64.10351)))
("SF_ARCHITECTURE" 0 ((12062.59468 67.87330) (12021.11572 64.10351) (11331.07183 64.10837) (11308.44740 67.87330)
(10961.53846 67.86708) (10938.91403 64.10351) (10822.02206 67.86708) (10803.16742 64.10837) (10686.27545 64.10837)
(10667.42081 67.86708) (10475.11312 67.86708) (10448.71889 64.10351)))
("SF_ARCHITECTURE" 0 ((10448.71889 -3.77070) (10467.57070 -3.77070) (12055.05238 -3.77070) (12066.36459 -3.77070)))
("SF_ARCHITECTURE" 0 ((10452.48869 5829.56267) (10505.27998 5829.56256) (10520.36199 5829.56256) (12039.97025
5829.56256)))
("SF_ARCHITECTURE" 0 ((12051.28201 2820.51278) (10452.48869 2820.51278)))
("SF_MASONRY_AND_ARCH" 0 ((10452.48869 2092.76018) (10452.48869 1628.95928) (10452.48869 1606.33484) (10452.48869
501.50735) (10452.48869 478.88292) (10452.48869 444.94627) (10452.48869 199.85011) (10452.48869 184.76527)))
("SF_ARCHITECTURE" 0 ((10452.48869 2092.76018) (10482.65554 2097.72862) (10542.98643 2152.94400) (10686.27545
2253.85226) (10848.41629 2336.80894) (10953.99604 2374.51618) (11044.49378 2398.04231) (11104.82749 2409.35452)
(11180.24038 2413.27274)))
("SF_ARCHITECTURE" 0 ((10520.36199 188.53790) (10509.04977 184.91369) (10452.48869 184.76527)))
("SF_SOLAR" 0 ((10467.57070 8133.48416) (10467.57070 8118.40113)))
("SF_SOLAR" 0 ((10467.57070 8084.46448) (10467.57070 8073.15226)))
("SF_SOLAR" 0 ((10467.57070 8050.52783) (10467.57070 8039.21561)))
("SF_SOLAR" 0 ((10467.57070 8016.59118) (10467.57070 8005.27896)))
("SF_SOLAR" 0 ((10471.34333 7971.34231) (10467.57070 7982.65452)))
("SF_SOLAR" 0 ((10467.57070 7963.80090) (10471.34333 7971.34231)))
("SF_SOLAR" 0 ((10467.57070 7926.09355) (10467.57070 7941.17647)))
("SF_SOLAR" 0 ((10490.19514 7971.34231) (10471.34333 7971.34231)))
("SF_ARCHITECTURE" 0 ((10475.11312 6840.12093) (10490.19514 6832.72749) (10614.62952 6832.57262) (10633.48416
6828.80871)))
("SF_ARCHITECTURE" 0 ((10475.11312 6840.12093) (10475.26086 6870.13190) (10478.88292 6874.05758)))
("SF_ARCHITECTURE" 0 ((10923.83201 6870.28631) (10904.97738 6866.52240) (10625.94174 6866.52240) (10603.31731
6870.28631) (10509.04977 6866.52240) (10478.88292 6874.05758)))
("SF_ARCHITECTURE" 0 ((10482.65554 7443.43891) (10478.88982 7413.27274) (10478.88292 6874.05758)))
("SF_ARCHITECTURE" 0 ((10697.58767 7492.45826) (10686.27545 7496.22296) (10486.42534 7496.07466) (10475.26776
7484.91697) (10475.26776 7450.98722) (10482.65554 7443.43891)))
("SF_ARCHITECTURE" 0 ((10697.58767 7473.60509) (10678.73303 7462.44729) (10569.38066 7462.58213) (10550.52885
7466.05679) (10512.81957 7462.14457) (10482.65554 7443.43891)))
("SF_SOLAR" 0 ((10493.96776 8133.48416) (10490.19514 8118.40113)))
("SF_SOLAR" 0 ((10490.19514 8009.04977) (10490.19514 8016.59118)))
("SF_SOLAR" 0 ((10490.19514 7971.34231) (10490.19514 7982.65452)))
("SF_SOLAR" 0 ((10490.19514 7971.34231) (10505.27998 7971.34231)))
("SF_SOLAR" 0 ((10497.73756 8084.46448) (10493.96776 8073.15226)))
("SF_SOLAR" 0 ((10493.96776 8050.52783) (10493.96776 8039.21561)))
("SF_ARCHITECTURE" 0 ((10501.50735 5690.04525) (11990.95023 5690.04525)))
("SF_ARCHITECTURE" 0 ((10505.27998 6451.73462) (10520.36199 6444.19955) (11134.99152 6444.19299)))
("SF_ARCHITECTURE" 0 ((10516.59219 6557.31550) (10509.19751 6542.23201) (10508.90204 6459.28258) (10505.27998
6451.73462)))
("SF_SOLAR" 0 ((10509.04977 8129.71335) (10512.81957 8118.40113)))
("SF_SOLAR" 0 ((10509.04977 8050.52783) (10509.04977 8042.98643)))
("SF_SOLAR" 0 ((10512.81957 8020.36199) (10520.36199 8005.27896)))
("SF_ARCHITECTURE" 0 ((10516.59219 6557.31550) (10886.12274 6557.31550)))
("SF_ARCHITECTURE" 0 ((10516.59219 6557.31550) (10517.64785 6636.50102) (10535.59242 6662.89593) (10561.68575
6689.29084) (10565.61086 6700.60305)))
("SF_SOLAR" 0 ((10520.36199 7982.65452) (10516.88767 7971.34887) (10520.36199 7963.80090)))
("SF_ARCHITECTURE" 0 ((10520.36199 188.53790) (10539.21663 184.76527) (10561.83348 184.91369) (10569.38066 188.53790)))
("SF_ARCHITECTURE" 0 ((11184.01301 2364.25339) (11134.99152 2360.33518) (11029.41176 2340.57952) (10916.28959
2306.49514) (10840.87387 2276.47670) (10686.27545 2197.29118) (10614.62952 2149.17353) (10576.92308 2111.76188)
(10517.79559 2062.59400) (10516.59219 207.38971) (10520.36199 188.53790)))
("SF_SOLAR" 0 ((10524.13179 7858.22025) (10524.13179 7899.69830)))
("SF_SOLAR" 0 ((10539.21663 7880.84468) (10531.67421 7880.84468)))
("SF_SOLAR" 0 ((10535.44400 8039.21561) (10535.44400 8050.52783)))
("SF_SOLAR" 0 ((10542.98643 8084.46448) (10542.98643 8069.38167)))
("SF_ARCHITECTURE" 0 ((10542.98643 6489.44186) (10592.00509 6489.29367) (10607.08993 6485.67115) (11123.67930
6485.67115) (11134.84446 6478.12308) (11141.47138 6466.81742) (11134.99152 6444.19299)))
("SF_SOLAR" 0 ((11191.55260 7918.55204) (11168.92817 7911.01708) (10569.38066 7908.43756) (10546.75622 7914.78133)))
("SF_SOLAR" 0 ((10558.06844 7899.69830) (10550.67658 7880.84468) (10550.52885 7858.22025)))
("SF_SOLAR" 0 ((10554.29864 8118.40113) (10558.06844 8133.48416)))
("SF_SOLAR" 0 ((10558.06844 7948.71799) (10565.61086 7937.40577)))
("SF_ARCHITECTURE" 0 ((10565.61086 6700.60305) (10590.94943 6715.69310) (10599.39910 6734.53971) (10599.54751
6757.16414)))
("SF_SOLAR" 0 ((10569.38066 8182.50385) (10569.38066 8174.96222)))
("SF_SOLAR" 0 ((10580.69287 7978.88394) (10569.38066 7990.19615)))
("SF_SOLAR" 0 ((10569.38066 7918.55204) (10581.75000 7944.79253) (10588.24152 7948.56335) (10720.21210 7948.72455)
(10739.06391 7952.48213) (10761.68835 7949.01403) (10773.00057 7952.48869)))
("SF_ARCHITECTURE" 0 ((10569.38066 188.53790) (10584.46550 184.76527) (11941.93020 184.77217) (11953.24242 188.53790)))
("SF_ARCHITECTURE" 0 ((10580.69378 241.32636) (10569.52907 222.47455) (10569.38066 188.53790)))
("SF_SOLAR" 0 ((10592.00509 8027.90339) (10576.92308 8027.90339)))
("SF_ARCHITECTURE" 0 ((10580.69378 241.32636) (10599.54751 237.55656) (10644.78948 237.55656) (10652.33880 237.55656)))
("SF_ARCHITECTURE" 0 ((10580.69378 241.32636) (10580.69378 2006.03292) (10588.38371 2019.91844) (10622.17195 2029.70758)
(10693.81505 2080.39853) (10776.77319 2129.41787) (10867.27093 2174.66674) (10931.37161 2194.57014)))
("SF_SOLAR" 0 ((10584.46459 8061.84016) (10586.34989 8061.84016) (10588.23529 8059.95475)))
("SF_SOLAR" 0 ((10614.62952 8065.61086) (10608.13869 8050.52783) (10588.23529 7956.25939)))
("SF_SOLAR" 0 ((10603.31731 8201.35747) (10602.26165 8178.73303) (10592.00509 8163.65000)))
("SF_SOLAR" 0 ((10592.00509 8084.46448) (10595.77771 8076.92308)))
("SF_ARCHITECTURE" 0 ((10595.77771 6602.56437) (10582.94717 6610.25362) (10592.00509 6636.50102)))
("SF_SOLAR" 0 ((10622.17195 7877.07387) (10599.54751 7877.07387)))
("SF_ARCHITECTURE" 0 ((10633.48416 6828.80871) (10637.10690 6813.72523) (10636.19830 6776.01810) (10625.93688
6762.13292) (10599.54751 6757.16414)))
("SF_SOLAR" 0 ((10607.08993 8129.71335) (10607.08993 8122.17195)))
("SF_SOLAR" 0 ((10788.08541 7993.96674) (10618.40215 7993.97330) (10607.08993 7997.73756)))
("SF_ARCHITECTURE" 0 ((10750.37613 7254.90170) (10698.63643 7183.25792) (10607.08993 7021.11640)))
("SF_SOLAR" 0 ((10610.85973 8223.98190) (10610.85973 8231.52330)))
("SF_SOLAR" 0 ((10614.62952 8174.96222) (10625.94174 8171.19163)))
("SF_SOLAR" 0 ((10810.70984 8061.84005) (10701.35747 8054.45317) (10690.04525 8057.92138) (10629.71437 8058.21753)
(10614.62952 8065.61086)))
("SF_SOLAR" 0 ((10614.62952 8065.61086) (10618.54989 8099.54751) (10633.33643 8148.56719) (10641.02658 8197.58665)))
("SF_SOLAR" 0 ((10799.39762 8027.90339) (10614.62952 8027.90339)))
("SF_ARCHITECTURE" 0 ((10833.33428 6610.10532) (10818.24943 6606.33507) (10795.62500 6610.09876) (10750.37613
6606.33507) (10727.75170 6610.09876) (10648.56618 6610.09876) (10622.17195 6602.56437)))
("SF_SOLAR" 0 ((10625.94174 7982.65452) (10625.94174 7967.57172)))
("SF_SOLAR" 0 ((10629.71437 8095.77670) (10636.42613 8102.95633) (10686.27545 8103.46629) (10697.58767 8107.08891)
(10705.12726 8103.31833) (10795.62500 8103.32489) (10814.47964 8107.08891)))
("SF_ARCHITECTURE" 0 ((10833.33428 6636.50102) (10799.39762 6640.26493) (10629.71437 6640.27149)))
("SF_ARCHITECTURE" 0 ((10886.12274 6557.31550) (10886.12964 6677.97862) (10889.74005 6693.06210) (10886.27115
6708.14480) (10886.12964 6764.70588) (10889.89536 6809.95475) (10885.96946 6825.03088) (10871.04072 6832.57262)
(10648.56618 6832.57262) (10633.48416 6828.80871)))
("SF_SOLAR" 0 ((10641.02658 8016.59118) (10637.25396 8005.27896)))
("SF_SOLAR" 0 ((10641.02658 8141.02557) (10822.02206 8141.01900) (10833.33428 8137.25498)))
("SF_SOLAR" 0 ((10731.52432 7967.57172) (10697.65667 7967.79050) (10686.72557 7971.64502) (10641.02658 7967.57172)))
("SF_SOLAR" 0 ((10840.87387 8163.65000) (10644.79638 8163.65000)))
("SF_ARCHITECTURE" 0 ((10761.68835 7337.85848) (10648.56618 7156.86301)))
("SF_ARCHITECTURE" 0 ((10648.56618 6677.97862) (10701.35747 6685.51380) (10776.77319 6685.37206) (10791.85520
6681.75645) (10825.79186 6685.51380) (10837.10407 6681.74989)))
("SF_SOLAR" 0 ((10656.10860 8084.46448) (10652.33880 8069.38167)))
("SF_ARCHITECTURE" 0 ((10652.33880 1972.09627) (10671.19061 1979.63801)))
("SF_ARCHITECTURE" 0 ((11248.11369 237.55656) (10667.42081 237.55656) (10652.33880 237.55656)))
("SF_ARCHITECTURE" 0 ((10652.33880 237.55656) (10648.56708 350.67873) (10663.64344 377.07296) (10663.65102 867.27093)))
("SF_ARCHITECTURE" 0 ((10656.10860 1666.66572) (10674.96233 1670.43835)))
("SF_ARCHITECTURE" 0 ((10656.10860 935.14423) (10652.48586 927.59491) (10648.56708 882.35294) (10663.65102 867.27093)))
("SF_SOLAR" 0 ((10659.87839 8122.17195) (10663.65102 8133.48416)))
("SF_ARCHITECTURE" 0 ((10674.96324 999.24491) (10659.87839 991.70532)))
("SF_ARCHITECTURE" 0 ((10663.65102 867.27093) (10682.65814 893.65826) (10693.81505 901.05226) (10991.70532 897.43495)
(11014.32975 901.20068) (11157.61595 901.20068) (11180.24038 897.43495)))
("SF_ARCHITECTURE" 0 ((10667.42081 6711.91527) (10701.35747 6723.07964) (10803.16742 6720.65475) (10837.10407
6726.99876)))
("SF_ARCHITECTURE" 0 ((10671.19061 1979.63801) (10674.96233 1670.43835)))
("SF_ARCHITECTURE" 0 ((10727.75170 2017.34514) (10671.19061 1979.63801)))
("SF_ARCHITECTURE" 0 ((10674.96324 999.24491) (10671.19751 1014.32975) (10674.96233 1670.43835)))
("SF_SOLAR" 0 ((10674.96324 8035.44502) (10674.96324 8042.98643)))
("SF_ARCHITECTURE" 0 ((10674.96324 999.24491) (11168.92817 999.24491)))
("SF_ARCHITECTURE" 0 ((10690.04525 6745.85192) (10697.59253 6749.47489) (10788.08541 6749.77104) (10833.33428
6760.93541)))
("SF_SOLAR" 0 ((10712.66968 8088.23529) (10694.18450 8087.86663) (10693.81505 8069.38167)))
("SF_SOLAR" 0 ((10693.81505 8005.27896) (10693.81505 8016.59118)))
("SF_SOLAR" 0 ((10697.58767 8122.17195) (10701.35747 8129.71335)))
("SF_ARCHITECTURE" 0 ((10697.58767 7492.45826) (10697.58767 7473.60509)))
("SF_ARCHITECTURE" 0 ((10697.58767 7492.45826) (10712.66968 7496.22296) (10912.51980 7496.22296) (10926.39695
7488.68122) (10927.59559 6900.45249) (10923.83201 6870.28631)))
("SF_ARCHITECTURE" 0 ((10697.58767 7473.60509) (10723.98190 7462.44072) (10769.23077 7462.29287)))
("SF_ARCHITECTURE" 0 ((10701.35747 938.91403) (10712.66968 942.67896) (11202.86482 942.68382)))
("SF_ARCHITECTURE" 0 ((10712.66968 3276.77251) (10720.21697 3273.14898) (10788.08541 3273.14898) (10818.24943
3288.08473)))
("SF_ARCHITECTURE" 0 ((10723.98190 3216.44016) (10701.36369 3217.64434) (10690.19367 3235.29412) (10691.25011
3261.68903) (10712.66968 3276.77251)))
("SF_ARCHITECTURE" 0 ((11783.55916 3276.77251) (11782.50271 5120.66324) (11757.01572 5154.59989) (11677.97930
5229.86708) (11621.41821 5274.20769) (11542.23133 5323.23394) (11478.13066 5353.39943) (11402.71493 5379.79502)
(11319.75962 5399.55034) (11251.88631 5407.23982) (11142.53394 5392.00860) (11082.20305 5376.01799) (11018.09955
5353.39943) (10923.83201 5308.15057) (10814.47964 5229.86708) (10742.98360 5158.37104) (10716.44038 5128.20554)
(10716.44038 5116.89333) (10712.66968 3276.77251)))
("SF_ARCHITECTURE" 0 ((10723.98190 3216.44016) (10731.67760 3186.27477) (10810.70984 3110.85973)))
("SF_ARCHITECTURE" 0 ((11760.93473 3220.21143) (11749.62251 3223.97568) (10742.83654 3223.97568) (10723.98190
3216.44016)))
("SF_ARCHITECTURE" 0 ((10723.98190 346.90803) (11131.22172 346.90803)))
("SF_SOLAR" 0 ((10731.52432 8069.38167) (10727.75170 8088.23529)))
("SF_ARCHITECTURE" 0 ((10735.29412 2023.00124) (10731.52432 2024.88688) (10727.75170 2017.34514)))
("SF_ARCHITECTURE" 0 ((10735.29412 2023.00124) (10727.75170 2017.34514)))
("SF_SOLAR" 0 ((10735.29412 8118.40113) (10742.83654 8133.48416)))
("SF_ARCHITECTURE" 0 ((10757.91855 2032.42862) (10746.60633 2022.17624) (10735.29412 2023.00124)))
("SF_ARCHITECTURE" 0 ((10754.14876 2043.74084) (10742.98982 2039.81493) (10735.29412 2023.00124)))
("SF_SOLAR" 0 ((10746.60633 7982.65452) (10746.60633 7971.34231)))
("SF_SOLAR" 0 ((10750.37613 7877.07387) (10765.46097 7877.07387)))
("SF_ARCHITECTURE" 0 ((10757.91855 2032.42862) (10754.14876 2043.74084)))
("SF_ARCHITECTURE" 0 ((10754.14876 2043.74084) (10765.45339 2053.84887) (10773.00057 2055.05305)))
("SF_ARCHITECTURE" 0 ((10757.91855 2032.42862) (10772.84729 2037.39706) (10776.77319 2047.51131)))
("SF_SOLAR" 0 ((10761.68835 8084.46448) (10765.46097 8069.38167)))
("SF_SOLAR" 0 ((10761.68835 7926.09355) (10761.68835 7937.40577) (10765.46097 7941.17647)))
("SF_SOLAR" 0 ((10769.23077 8039.21561) (10769.23077 8046.75724)))
("SF_SOLAR" 0 ((10984.16290 7952.48869) (10965.30826 7948.71799) (10863.49830 7948.72455) (10840.87387 7952.48869)
(10780.54989 7949.01403) (10773.00057 7952.48869)))
("SF_SOLAR" 0 ((10788.08541 7993.96674) (10784.31278 7986.42534) (10774.19921 7967.57172) (10773.00057 7952.48869)))
("SF_ARCHITECTURE" 0 ((10773.00057 2055.05305) (10776.77319 2047.51131)))
("SF_ARCHITECTURE" 0 ((10791.85520 2066.36527) (10780.54921 2065.16109) (10773.00057 2055.05305)))
("SF_SOLAR" 0 ((10776.77319 7877.07387) (10840.87387 7877.07387)))
("SF_ARCHITECTURE" 0 ((10795.62500 2055.05305) (10791.70057 2048.70928) (10776.77319 2047.51131)))
("SF_SOLAR" 0 ((10788.08541 7993.96674) (10814.47964 7990.19615)))
("SF_SOLAR" 0 ((10788.08541 7993.96674) (10791.85520 8016.59118)))
("SF_SOLAR" 0 ((10795.62500 8133.48416) (10791.85520 8118.40113)))
("SF_ARCHITECTURE" 0 ((10795.62500 2055.05305) (10791.85520 2066.36527)))
("SF_ARCHITECTURE" 0 ((10810.70984 2077.67749) (10795.78032 2072.85679) (10791.85520 2066.36527)))
("SF_ARCHITECTURE" 0 ((10814.47964 2066.36527) (10810.55452 2060.01459) (10795.62500 2055.05305)))
("SF_SOLAR" 0 ((10799.39762 8027.90339) (10825.79186 8027.90339)))
("SF_SOLAR" 0 ((10799.39762 8027.90339) (10803.16742 8050.52783)))
("SF_ARCHITECTURE" 0 ((10799.39762 5082.95667) (10803.32206 5076.46482) (10814.47964 5071.64446)))
("SF_SOLAR" 0 ((10810.70984 8061.84005) (10833.33428 8061.84005)))
("SF_SOLAR" 0 ((10810.70984 8061.84005) (10819.30034 8099.54751) (10833.33428 8137.25498)))
("SF_SOLAR" 0 ((10987.93269 7993.96674) (10829.56923 7993.81210) (10823.07771 7990.04140) (10810.70984 7960.03020)))
("SF_ARCHITECTURE" 0 ((10810.70984 3110.85973) (10811.91324 3084.47104) (10825.79186 3073.15238) (10837.10407
3073.15238) (10863.49830 3073.15238) (11666.66708 3073.15238) (11684.31618 3080.84819) (11685.52036 3110.85973)))
("SF_ARCHITECTURE" 0 ((10810.70984 3110.85973) (10829.56165 3114.62398) (11553.54355 3114.63643) (11576.16934
3118.40147) (11628.95928 3118.25373) (11685.52036 3110.85973)))
("SF_ARCHITECTURE" 0 ((10814.47964 2066.36527) (10810.70984 2077.67749)))
("SF_ARCHITECTURE" 0 ((10810.70984 2077.67749) (10822.02206 2087.78552) (10837.10407 2088.98971)))
("SF_SOLAR" 0 ((10814.47964 8182.50385) (10814.47964 8174.96222)))
("SF_ARCHITECTURE" 0 ((10818.24943 4355.20362) (10814.48586 4366.51584) (10814.47964 5071.64446)))
("SF_ARCHITECTURE" 0 ((11677.97930 5067.87330) (11662.89593 5075.56278) (11632.73043 5105.43269) (11583.71041
5142.24468) (11481.90045 5198.65803) (11383.86029 5232.72998) (11308.44740 5245.09140) (11172.70079 5244.94977)
(11123.67930 5236.50679) (11074.66063 5221.42398) (10965.30826 5176.17477) (10878.58314 5119.61403) (10825.79186
5076.47104) (10814.47964 5071.64446)))
("SF_ARCHITECTURE" 0 ((10814.47964 2066.36527) (10833.17896 2071.33292) (10837.10407 2077.67749)))
("SF_ARCHITECTURE" 0 ((11677.97885 4355.20362) (11383.86029 4355.20362) (11361.23586 4355.20362) (11300.90498
4355.20362) (11285.82296 4355.20362) (10818.24943 4355.20362)))
("SF_ARCHITECTURE" 0 ((10818.24943 4355.20362) (10814.47964 4328.80803) (10814.48586 3303.16742) (10818.24943
3288.08473)))
("SF_ARCHITECTURE" 0 ((11670.43699 3280.54299) (11640.27149 3273.00747) (10867.27093 3273.00747) (10833.33428
3277.82885) (10818.24943 3288.08473)))
("SF_SOLAR" 0 ((10829.56165 8001.50837) (10834.38993 8031.67421) (10844.64649 8058.06946)))
("SF_SOLAR" 0 ((10840.87387 8163.65000) (10833.33428 8137.25498)))
("SF_SOLAR" 0 ((10833.33428 8103.31833) (10840.87387 8099.54751)))
("SF_ARCHITECTURE" 0 ((10837.10407 7462.29287) (10852.18609 7465.76753) (10889.89536 7458.52161)))
("SF_ARCHITECTURE" 0 ((10837.10407 2088.98971) (10837.10407 2077.67749)))
("SF_ARCHITECTURE" 0 ((10837.10407 2088.98971) (10844.65136 2099.09774) (10859.72851 2100.30192)))
("SF_ARCHITECTURE" 0 ((10859.72851 2088.98971) (10855.80339 2082.64514) (10837.10407 2077.67749)))
("SF_SOLAR" 0 ((10840.87387 8163.65000) (10855.95871 8171.03688) (10870.88609 8166.22308) (10874.80430 8156.10848)
(10869.99129 8133.48416) (10857.15588 8107.08891) (10850.97919 8076.92624) (10841.39174 8066.45317) (10844.64649
8058.06946)))
("SF_SOLAR" 0 ((11018.09955 8054.29864) (11009.50837 8035.45158) (10999.24491 8028.05814) (10840.87387 8027.90339)))
("SF_SOLAR" 0 ((11025.64197 8061.84005) (10844.64649 8058.06946)))
("SF_SOLAR" 0 ((10863.49830 8141.02557) (10845.84989 8137.10023) (10848.41629 8118.40113)))
("SF_ARCHITECTURE" 0 ((10848.41629 1289.59276) (10854.91471 1293.51787) (10913.56855 1383.86029) (10934.09333
1406.48473) (10974.04864 1474.21097) (10990.65441 1489.44287) (11025.64197 1546.00396)))
("SF_SOLAR" 0 ((10855.95871 8197.58665) (10852.18609 8190.04525)))
("SF_SOLAR" 0 ((10852.18609 7978.88394) (10852.18609 7967.57172)))
("SF_ARCHITECTURE" 0 ((10859.72851 2088.98971) (10859.72851 2100.30192)))
("SF_ARCHITECTURE" 0 ((10882.35294 2111.61414) (10867.27579 2110.40995) (10859.72851 2100.30192)))
("SF_ARCHITECTURE" 0 ((10886.12274 2100.30192) (10878.57557 2093.95735) (10859.72851 2088.98971)))
("SF_SOLAR" 0 ((10863.49830 8001.50837) (10867.27093 8012.82059)))
("SF_SOLAR" 0 ((11052.03620 8133.48416) (11045.69242 8129.55871) (11041.61878 8114.63066) (11033.17670 8105.42410)
(10984.16290 8099.55407) (10882.35294 8103.31821) (10867.27093 8099.54751)))
("SF_ARCHITECTURE" 0 ((10867.27093 5011.31222) (10867.27093 4457.01357)))
("SF_ARCHITECTURE" 0 ((10867.27093 5011.31222) (10855.95781 5018.86018) (10855.95781 5033.93665) (10867.41176
5048.86505) (10874.81052 5052.78993)))
("SF_ARCHITECTURE" 0 ((10867.27093 5011.31222) (10884.91934 5030.16550) (10886.12274 5041.47771)))
("SF_ARCHITECTURE" 0 ((10867.27093 4457.01357) (10881.14808 4445.70136) (10887.32138 4419.30645) (10897.43495
4407.99355)))
("SF_ARCHITECTURE" 0 ((10867.27093 4457.01357) (10855.95781 4453.08846) (10855.95781 4430.61799) (10855.95781
4411.76471) (10855.95781 4400.60713) (10882.35294 4396.83631) (10897.43495 4407.99355)))
("SF_SOLAR" 0 ((10874.81052 8039.21561) (10878.58314 8046.75724)))
("SF_ARCHITECTURE" 0 ((10874.81052 5052.78993) (10886.12274 5041.47771)))
("SF_ARCHITECTURE" 0 ((10874.81052 5052.78993) (10874.81052 5056.56109) (10886.12274 5064.10215)))
("SF_SOLAR" 0 ((11055.80600 8163.65000) (10882.35294 8163.65000)))
("SF_SOLAR" 0 ((10952.11256 8141.02557) (10923.83201 8144.64186) (10882.35294 8141.02557)))
("SF_SOLAR" 0 ((10882.35294 7926.09355) (10882.35294 7941.17647)))
("SF_ARCHITECTURE" 0 ((10882.35294 2111.61414) (10886.12274 2100.30192)))
("SF_ARCHITECTURE" 0 ((10908.74717 2122.92636) (10893.66516 2121.86991) (10882.35294 2111.61414)))
("SF_SOLAR" 0 ((10886.12274 8069.38167) (10886.12274 8084.46448)))
("SF_ARCHITECTURE" 0 ((10886.12274 6557.31550) (10920.05452 6557.46335) (10927.60181 6561.08597)))
("SF_ARCHITECTURE" 0 ((10886.12274 5064.10215) (10897.43495 5052.78993)))
("SF_ARCHITECTURE" 0 ((10904.97738 5075.41437) (10897.43009 5074.21052) (10886.12274 5064.10215)))
("SF_ARCHITECTURE" 0 ((10886.12274 5041.47771) (10893.51742 5042.68247) (10897.43495 5052.78993)))
("SF_ARCHITECTURE" 0 ((10912.51980 2111.61414) (10908.59389 2105.27036) (10886.12274 2100.30192)))
("SF_SOLAR" 0 ((10889.89536 7978.88394) (10889.89536 7963.80090)))
("SF_SOLAR" 0 ((10897.43495 7877.07387) (10889.89536 7877.07387)))
("SF_SOLAR" 0 ((10901.20758 8133.48416) (10897.43495 8114.63054)))
("SF_ARCHITECTURE" 0 ((10916.28959 5064.10215) (10904.98360 5053.99468) (10897.43495 5052.78993)))
("SF_ARCHITECTURE" 0 ((11214.17704 4407.99355) (10897.43495 4407.99355)))
("SF_SOLAR" 0 ((10901.20758 8005.27896) (10908.74717 8020.36199)))
("SF_ARCHITECTURE" 0 ((10953.99604 1546.00396) (10943.73405 1538.31312) (10901.20758 1478.13066)))
("SF_SOLAR" 0 ((10904.97738 7975.11312) (10908.74717 7971.34231) (10904.97738 7963.80090)))
("SF_ARCHITECTURE" 0 ((10904.97738 5075.41437) (10916.28959 5064.10215)))
("SF_ARCHITECTURE" 0 ((10904.97738 5075.41437) (10912.51980 5085.52274) (10920.05939 5086.72658)))
("SF_ARCHITECTURE" 0 ((10935.14423 4264.70588) (10923.83201 4275.86346) (10904.97738 4272.24695)))
("SF_ARCHITECTURE" 0 ((10912.51980 2111.61414) (10908.74717 2122.92636)))
("SF_ARCHITECTURE" 0 ((10908.74717 2122.92636) (10920.05939 2133.18213) (10942.68382 2134.23857)))
("SF_SOLAR" 0 ((10912.51980 8035.44502) (10912.51980 8046.75724)))
("SF_ARCHITECTURE" 0 ((10912.51980 2111.61414) (10931.37161 2112.67048) (10946.45645 2122.92636)))
("SF_ARCHITECTURE" 0 ((10916.28959 5064.10215) (10927.60181 5079.18552)))
("SF_SOLAR" 0 ((10920.05939 8088.23529) (10920.05939 8069.38167)))
("SF_ARCHITECTURE" 0 ((10920.05939 5086.72658) (10927.60181 5079.18552)))
("SF_ARCHITECTURE" 0 ((10920.05939 5086.72658) (10927.60181 5096.83495) (10935.14423 5098.03880)))
("SF_ARCHITECTURE" 0 ((10927.60181 6561.08597) (10931.35916 6828.80871) (10923.83201 6870.28631)))
("SF_ARCHITECTURE" 0 ((10927.60181 6561.08597) (10942.68382 6557.32206) (11033.18247 6557.31550)))
("SF_ARCHITECTURE" 0 ((10938.91403 5086.72658) (10935.14423 5079.18552) (10927.60181 5079.18552)))
("SF_SOLAR" 0 ((10935.14423 8012.82059) (10931.37161 8001.50837)))
("SF_ARCHITECTURE" 0 ((10953.99604 2183.25792) (10938.92093 2184.46210) (10931.37161 2194.57014)))
("SF_ARCHITECTURE" 0 ((11248.11369 2258.67296) (11153.84615 2254.75396) (11059.57862 2239.67127) (10972.85068
2216.13824) (10938.92093 2203.00667) (10931.37161 2194.57014)))
("SF_SOLAR" 0 ((10935.14423 8125.94276) (10935.14423 8114.63054)))
("SF_ARCHITECTURE" 0 ((10938.91403 5086.72658) (10935.14423 5098.03880)))
("SF_ARCHITECTURE" 0 ((10935.14423 5098.03880) (10942.69140 5108.15373) (10961.53846 5113.12217)))
("SF_ARCHITECTURE" 0 ((10938.91403 5086.72658) (10953.84276 5094.41674) (10961.53846 5113.12217)))
("SF_ARCHITECTURE" 0 ((10942.68382 2134.23857) (10946.45645 2122.92636)))
("SF_ARCHITECTURE" 0 ((10976.62048 2145.55079) (10950.23314 2144.34661) (10942.68382 2134.23857)))
("SF_ARCHITECTURE" 0 ((10946.45645 2122.92636) (10968.93247 2127.89400) (10976.62048 2134.23857)))
("SF_SOLAR" 0 ((10952.11256 8141.02557) (10950.22624 8122.17195)))
("SF_SOLAR" 0 ((10950.22624 8039.21561) (10950.22624 8046.75724)))
("SF_SOLAR" 0 ((11044.49378 8141.02557) (10952.11256 8141.02557)))
("SF_SOLAR" 0 ((10952.11256 8141.02557) (10953.99604 8152.33778)))
("SF_SOLAR" 0 ((10953.99604 8073.15226) (10953.99604 8084.46448)))
("SF_SOLAR" 0 ((10953.99604 7963.80090) (10953.99604 7982.65452)))
("SF_ARCHITECTURE" 0 ((10953.99604 1546.00396) (10961.53846 1534.69174)))
("SF_ARCHITECTURE" 0 ((10953.99604 1546.00396) (10957.92602 1557.15735) (10968.71765 1561.44774) (10992.75407
1606.33484) (11028.35543 1651.58371) (11082.20305 1738.31165)))
("SF_ARCHITECTURE" 0 ((11214.17704 4407.99355) (11217.94876 4426.84808) (11216.74480 5196.07195) (11206.63744
5203.46527) (11180.24038 5203.47183) (11127.45192 5191.25792) (11063.34842 5168.49219) (10961.53846 5113.12217)))
("SF_ARCHITECTURE" 0 ((10965.30826 4573.90690) (11007.83676 4638.00905) (11066.06946 4709.65351) (11093.51527
4751.13122)))
("SF_SOLAR" 0 ((10976.62048 8016.59118) (10972.85068 8005.27896)))
("SF_SOLAR" 0 ((10976.62048 7941.17647) (10972.85068 7922.32274)))
("SF_ARCHITECTURE" 0 ((10972.85068 3318.25034) (11414.02715 3322.02138)))
("SF_SOLAR" 0 ((10976.62048 8114.63054) (10987.93269 8133.48416)))
("SF_SOLAR" 0 ((10976.62048 8069.38167) (10976.62048 8088.23529)))
("SF_SOLAR" 0 ((10976.62048 8050.52783) (10976.62048 8039.21561)))
("SF_ARCHITECTURE" 0 ((10976.62048 2145.55079) (10976.62048 2134.23857)))
("SF_ARCHITECTURE" 0 ((10976.62048 2145.55079) (10991.70532 2156.70837) (11014.32975 2153.09174)))
("SF_ARCHITECTURE" 0 ((10976.62048 2134.23857) (11003.01753 2139.21324) (11014.32975 2153.09174)))
("SF_SOLAR" 0 ((10984.16290 7952.48869) (11006.78733 7948.71799)))
("SF_SOLAR" 0 ((10999.24491 7997.73756) (10985.21923 7967.57172) (10984.16290 7952.48869)))
("SF_ARCHITECTURE" 0 ((10984.16290 2190.79966) (10999.24491 2190.79966)))
("SF_SOLAR" 0 ((10999.24491 8088.23529) (10999.24491 8073.15226)))
("SF_SOLAR" 0 ((10999.24491 7997.73756) (11021.86934 7993.96674)))
("SF_SOLAR" 0 ((10999.24491 7997.73756) (11003.01753 8020.36199)))
("SF_SOLAR" 0 ((10999.24491 7975.11312) (11003.01753 7960.03020)))
("SF_SOLAR" 0 ((11006.78733 7937.40577) (11006.78733 7948.71799)))
("SF_SOLAR" 0 ((11184.01301 7944.94717) (11176.46369 7948.56991) (11108.59729 7948.86606) (11093.51527 7952.48213)
(11006.78733 7948.71799)))
("SF_SOLAR" 0 ((11010.55713 8118.40113) (11010.55713 8125.94276) (11018.09955 8133.48416)))
("SF_ARCHITECTURE" 0 ((11010.55713 791.85520) (11021.86934 791.85520)))
("SF_ARCHITECTURE" 0 ((11055.80600 4773.75566) (11020.82059 4721.11968) (11014.32975 4717.19457)))
("SF_ARCHITECTURE" 0 ((11063.34842 2164.40396) (11014.32975 2153.09174)))
("SF_SOLAR" 0 ((11018.09955 8027.90339) (11036.95419 8027.90339)))
("SF_SOLAR" 0 ((11018.09955 7963.80090) (11036.95419 7993.96674)))
("SF_ARCHITECTURE" 0 ((11052.03620 2202.11188) (11021.86934 2202.11188)))
("SF_SOLAR" 0 ((11025.64197 8061.84005) (11044.49378 8061.84005)))
("SF_SOLAR" 0 ((11025.64197 8061.84005) (11033.18156 8095.77670)))
("SF_ARCHITECTURE" 0 ((11025.64197 5260.18100) (11040.72398 5263.95215)))
("SF_ARCHITECTURE" 0 ((11085.97285 6561.08597) (11078.42557 6557.46335) (11033.18247 6557.31550)))
("SF_SOLAR" 0 ((11202.86482 7993.96674) (11036.95419 7993.96674)))
("SF_SOLAR" 0 ((11048.26640 8027.90339) (11036.95419 7993.96674)))
("SF_SOLAR" 0 ((11040.72398 8190.04525) (11040.72398 8197.58665)))
("SF_ARCHITECTURE" 0 ((11040.78846 817.04683) (11040.72398 818.24943)))
("SF_ARCHITECTURE" 1 ((11040.78846 817.04683) (10833.33428 817.05226) (10791.85520 814.32500) (10776.92647 803.16742)
(10773.00147 791.85520) (10773.00147 765.46097) (10773.00147 731.52432) (10773.00147 712.66968) (10773.00147 482.65554)
(10774.20543 441.17647) (10784.31278 430.01889) (10795.62500 426.10068) (10822.02206 429.85735) (10840.87387 426.09932)
(11018.09955 426.09932) (11067.11821 430.01889) (11077.22704 437.41154) (11080.10204 799.39762) (11077.23326 810.70226)
(11070.88326 817.04604)))
("SF_ARCHITECTURE" 0 ((11055.80600 478.88292) (11055.65271 780.54299) (11041.92885 795.77342) (11040.78846 817.04683)))
("SF_SOLAR" 0 ((11048.26640 8103.31833) (11059.57862 8099.54751)))
("SF_SOLAR" 0 ((11048.26640 8027.90339) (11217.94966 8027.90339)))
("SF_SOLAR" 0 ((11048.26640 8027.90339) (11059.57862 8061.84005)))
("SF_SOLAR" 0 ((11052.03620 8133.48416) (11070.89084 8118.40113)))
("SF_SOLAR" 0 ((11052.03620 8133.48416) (11055.80600 8163.65000)))
("SF_ARCHITECTURE" 0 ((11052.03620 5267.72206) (11127.45192 5290.19864) (11221.71946 5301.65871) (11270.73812
5301.51086) (11300.90498 5294.26572) (11353.69627 5290.19864) (11440.42138 5267.72206)))
("SF_ARCHITECTURE" 0 ((11059.57862 467.57070) (11052.03620 460.03111)))
("SF_SOLAR" 0 ((11055.80600 8163.65000) (11070.89084 8174.96222)))
("SF_ARCHITECTURE" 0 ((11063.34842 4762.44344) (11055.80600 4773.75566)))
("SF_ARCHITECTURE" 0 ((11055.80600 4773.75566) (11057.01086 4781.30362) (11067.11821 4792.60894)))
("SF_SOLAR" 0 ((11059.57862 8061.84005) (11233.03167 8061.84005)))
("SF_SOLAR" 0 ((11059.57862 8061.84005) (11058.05407 8065.76550) (11081.15215 8125.94276) (11082.20305 8141.02557)))
("SF_SOLAR" 0 ((11059.57862 7982.65452) (11059.57862 7967.57172)))
("SF_ARCHITECTURE" 0 ((11063.34842 2164.40396) (11070.89570 2158.06086) (11097.27885 2161.83767) (11108.59729
2175.71618)))
("SF_ARCHITECTURE" 0 ((11063.34842 2164.40396) (11078.43043 2179.33281) (11101.05000 2179.33971) (11108.59729
2175.71618)))
("SF_ARCHITECTURE" 0 ((11074.66063 4773.75566) (11067.11821 4792.60894)))
("SF_ARCHITECTURE" 0 ((11078.43043 4811.46346) (11071.93959 4807.53767) (11067.11821 4792.60894)))
("SF_SOLAR" 0 ((11089.74265 8163.65000) (11070.89084 8174.96222)))
("SF_SOLAR" 0 ((11078.43043 8197.58665) (11070.89084 8174.96222)))
("SF_SOLAR" 0 ((11082.20305 8141.02557) (11070.89084 8141.02557)))
("SF_SOLAR" 0 ((11070.89084 8005.27896) (11070.89084 8012.82059) (11078.43043 8020.36199)))
("SF_ARCHITECTURE" 0 ((11078.43043 4811.46346) (11089.74265 4803.92115)))
("SF_ARCHITECTURE" 0 ((11078.43043 4811.46346) (11079.63529 4819.00452) (11089.74265 4826.54559)))
("SF_SOLAR" 0 ((11082.20305 8141.02557) (11088.54548 8148.57376) (11089.74265 8163.65000)))
("SF_SOLAR" 0 ((11082.20305 8039.21561) (11085.97285 8050.52783)))
("SF_SOLAR" 0 ((11248.11369 8110.85973) (11225.48925 8099.84367) (11214.17704 8103.02217) (11202.86482 8099.69548)
(11153.84615 8099.55407) (11134.99152 8103.16369) (11119.90950 8099.56063) (11085.97285 8103.31833)))
("SF_ARCHITECTURE" 0 ((12006.03360 6557.31527) (11383.86029 6557.31527) (11369.97624 6549.62545) (11365.15554
6534.69106) (11365.00090 6406.48575) (11361.08258 6396.37771) (11217.94966 6395.18009) (11207.83462 6399.09876)
(11203.01324 6414.02715) (11206.63744 6478.12964) (11202.87240 6504.52489) (11206.62986 6538.46154) (11202.71154
6549.76719) (11191.55260 6557.16063) (11097.28507 6557.32206) (11085.97285 6561.08597)))
("SF_ARCHITECTURE" 0 ((11089.74355 7571.64400) (11085.97285 6561.08597)))
("SF_SOLAR" 0 ((11270.73812 8163.65000) (11089.74265 8163.65000)))
("SF_ARCHITECTURE" 0 ((11089.74265 4826.54559) (11097.28507 4826.54559)))
("SF_ARCHITECTURE" 0 ((11089.74265 4826.54559) (11090.94751 4837.85158) (11101.05486 4845.40011)))
("SF_ARCHITECTURE" 0 ((11089.74265 4796.38009) (11089.74265 4803.92115)))
("SF_ARCHITECTURE" 0 ((11089.74265 4803.92115) (11096.08710 4811.46968) (11097.28507 4826.54559)))
("SF_ARCHITECTURE" 0 ((12156.86233 7631.97590) (12145.55011 7635.74005) (11704.37364 7635.75317) (11685.52036
7639.51075) (11089.74355 7639.51731)))
("SF_ARCHITECTURE" 0 ((11089.74355 7571.64400) (11089.74355 7639.51731)))
("SF_ARCHITECTURE" 0 ((11089.74355 7571.64400) (12100.30124 7571.63744) (12115.38462 7568.16934) (12156.86233
7571.79208) (12175.71686 7579.18552)))
("SF_SOLAR" 0 ((11263.19853 8141.02557) (11244.34389 8144.78971) (11221.71946 8141.03213) (11097.28507 8141.02557)))
("SF_ARCHITECTURE" 0 ((11108.59729 4841.62896) (11107.39242 4834.08790) (11097.28507 4826.54559)))
("SF_SOLAR" 0 ((11104.82749 8182.50385) (11101.05486 8174.96222)))
("SF_ARCHITECTURE" 0 ((11101.05486 4852.94118) (11101.05486 4845.40011)))
("SF_ARCHITECTURE" 0 ((11101.05486 4845.40011) (11108.59729 4841.62896)))
("SF_ARCHITECTURE" 0 ((11157.61595 4909.50226) (11124.73643 4864.25339) (11118.71154 4849.17692) (11108.59729
4841.62896)))
("SF_ARCHITECTURE" 0 ((11187.78281 1029.41176) (11187.78903 1112.36708) (11191.54774 1131.22172) (11191.40554
2130.46731) (11187.62817 2168.17523) (11180.23552 2178.28326) (11134.99152 2179.48122) (11108.59729 2175.71618)))
("SF_SOLAR" 0 ((11112.36708 8118.40113) (11112.36708 8129.71335)))
("SF_SOLAR" 0 ((11134.99152 7971.34231) (11116.29299 7968.77602) (11112.36708 7982.65452)))
("SF_SOLAR" 0 ((11138.76414 8118.40113) (11134.99152 8133.48416)))
("SF_SOLAR" 0 ((11134.99152 8005.27896) (11134.99152 8020.36199)))
("SF_SOLAR" 0 ((11134.99152 7971.34231) (11134.99152 7978.88394)))
("SF_SOLAR" 0 ((11134.99152 7971.34231) (11153.84615 7971.34231)))
("SF_SOLAR" 0 ((11134.99152 7858.22025) (11134.99152 7869.53247)))
("SF_ARCHITECTURE" 0 ((11429.10916 6444.19310) (11428.95588 6346.15385) (11421.56199 6336.04615) (11410.25735
6334.84163) (11150.07636 6336.04615) (11138.91742 6349.92466) (11134.99152 6444.19299)))
("SF_SOLAR" 0 ((11153.84615 7971.34231) (11157.61595 7960.03020)))
("SF_SOLAR" 0 ((11153.84615 7971.34231) (11157.61595 7978.88394)))
("SF_SOLAR" 0 ((11157.61595 8046.75724) (11157.61595 8039.21561)))
("SF_SOLAR" 0 ((11157.61595 8020.36199) (11157.61595 8005.27896)))
("SF_ARCHITECTURE" 0 ((11157.61595 3465.30894) (11215.23416 3559.57794) (11250.82919 3597.28507) (11349.92364
3748.11505)))
("SF_ARCHITECTURE" 0 ((11168.92817 999.24491) (11180.24038 988.08801) (11191.55260 988.98982) (11201.65452 995.62353)
(11202.86572 1021.86448) (11187.78281 1029.41176)))
("SF_ARCHITECTURE" 0 ((11168.92817 999.24491) (11187.78281 1029.41176)))
("SF_SOLAR" 0 ((11172.70079 8110.85973) (11184.01301 8114.62387) (11199.09502 8110.85973)))
("SF_SOLAR" 0 ((11180.24038 7895.92760) (11180.09333 7880.84468) (11172.70079 7861.99095)))
("SF_SOLAR" 0 ((11176.47059 7978.88394) (11180.24038 7986.42534)))
("SF_SOLAR" 0 ((11180.24038 8122.17195) (11184.01301 8133.48416)))
("SF_SOLAR" 0 ((11180.24038 8069.38167) (11180.24038 8084.46448)))
("SF_SOLAR" 0 ((11180.24038 8039.21561) (11180.24038 8050.52783)))
("SF_SOLAR" 0 ((11180.24038 8005.27896) (11180.24038 8016.59118)))
("SF_ARCHITECTURE" 0 ((11184.01301 2364.25339) (11187.63507 2394.41957) (11180.24038 2413.27274)))
("SF_ARCHITECTURE" 0 ((11180.24038 2413.27274) (11180.09333 2439.66844) (11165.16459 2533.93665) (11166.36324
2560.17692) (11176.47059 2564.09593) (11331.07183 2564.09593) (11342.22873 2560.17692) (11345.99921 2552.79061)
(11346.00611 2526.39491) (11331.21889 2443.43891) (11331.07183 2417.04400)))
("SF_ARCHITECTURE" 0 ((11191.55260 848.41629) (11202.86572 863.49830) (11202.86572 889.88778) (11195.16991 896.23156)
(11180.24038 897.43495)))
("SF_ARCHITECTURE" 0 ((11191.55260 848.41629) (11185.21018 852.34140) (11180.38880 871.04072) (11180.24038 897.43495)))
("SF_ARCHITECTURE" 0 ((11184.01301 2364.25339) (11191.70102 2349.32534) (11206.63744 2345.39943) (11308.44740
2345.55407) (11319.75204 2352.94740) (11327.29921 2364.25339)))
("SF_SOLAR" 0 ((11191.55260 7918.55204) (11198.26584 7911.37262) (11206.56561 7911.10090) (11225.48925 7922.32274)))
("SF_SOLAR" 0 ((11191.55260 7918.55204) (11192.60973 7944.94717) (11297.13518 8197.58665)))
("SF_ARCHITECTURE" 0 ((11202.86572 339.36652) (11187.78971 369.53337) (11187.78903 467.57070) (11191.55260 490.19514)
(11191.54774 803.16742) (11187.79525 822.02206) (11191.55260 848.41629)))
("SF_SOLAR" 0 ((11202.86482 8050.52783) (11202.86482 8039.21561)))
("SF_ARCHITECTURE" 0 ((11202.86572 286.57523) (11202.86572 312.97229)))
("SF_SOLAR" 0 ((11206.63744 8084.46448) (11210.40724 8080.69389) (11210.40724 8069.38167)))
("SF_SOLAR" 0 ((11236.80147 7911.01052) (11215.38190 7895.92104) (11206.63744 7858.22025)))
("SF_ARCHITECTURE" 0 ((11214.17704 4407.99355) (11225.48925 4400.45249)))
("SF_ARCHITECTURE" 0 ((11221.71946 3672.69943) (11260.47613 3729.10656) (11270.73812 3733.03167)))
("SF_SOLAR" 0 ((11225.48925 8133.48416) (11225.48925 8118.40113)))
("SF_SOLAR" 0 ((11225.48925 7922.32274) (11236.80147 7911.01052)))
("SF_SOLAR" 0 ((11240.57410 7948.71799) (11230.31063 7937.40566) (11225.48925 7922.32274)))
("SF_SOLAR" 0 ((11236.80147 7911.01052) (11704.37364 7908.43756) (11930.61799 7911.01708) (11960.78473 7914.78133)))
("SF_SOLAR" 0 ((11240.57410 7948.71799) (11241.62975 7963.80090) (11269.68247 8027.90339) (11271.79525 8042.98643)
(11326.24355 8167.42081) (11327.29921 8196.32986)))
("SF_SOLAR" 0 ((11240.57410 7948.71799) (11447.96380 7949.92229) (11469.53880 7978.88394) (11508.29468 8058.06946)))
("SF_ARCHITECTURE" 0 ((11248.11369 2258.67296) (11357.46606 2254.75396) (11451.73360 2239.67127) (11613.87590
2193.51380) (11693.06143 2157.75781) (11817.49581 2091.71075) (11915.53586 2027.60792) (11929.41380 2013.57466)
(11926.69344 245.10385) (11919.29887 237.71120) (11858.98167 237.70430) (11851.43247 241.32636)))
("SF_ARCHITECTURE" 0 ((11248.11369 237.55656) (11248.12059 852.18609) (11251.88631 874.81052) (11248.11369 965.30826)
(11251.87941 1006.78733) (11248.11459 1255.65611) (11248.11459 1278.28054) (11248.11459 1357.46606) (11248.11459
1372.54808) (11251.87941 1576.16799) (11248.11369 1598.79242) (11248.11459 1628.95928) (11248.11459 1828.80871)
(11248.11459 1851.43314) (11248.11459 1911.76471) (11248.11459 1926.84740) (11251.87941 2239.81900) (11248.11369
2258.67296)))
("SF_ARCHITECTURE" 0 ((11248.11369 237.55656) (11840.12025 237.56278) (11851.43247 241.32636)))
("SF_ARCHITECTURE" 0 ((11248.11459 5041.47771) (11248.11459 5154.59989)))
("SF_ARCHITECTURE" 0 ((11289.59276 4407.99355) (11278.28054 4397.88609) (11259.42590 4393.06538) (11248.11459
4394.11527) (11248.11459 4400.45871) (11248.11459 4815.23337)))
("SF_SOLAR" 0 ((11263.19853 8050.52783) (11251.88631 8054.29864)))
("SF_SOLAR" 0 ((11466.81844 7993.96674) (11266.96833 7993.96674)))
("SF_SOLAR" 0 ((11266.96833 7877.07387) (11300.90498 7877.07387)))
("SF_ARCHITECTURE" 0 ((11282.05034 3733.03167) (11270.73812 3733.03167)))
("SF_ARCHITECTURE" 0 ((11282.05034 3755.65611) (11273.61448 3748.10814) (11270.73812 3733.03167)))
("SF_SOLAR" 0 ((11278.28054 8114.63054) (11282.05034 8107.08891) (11285.82296 8107.08891)))
("SF_SOLAR" 0 ((11278.28054 8027.90339) (11485.67025 8027.90339)))
("SF_ARCHITECTURE" 0 ((11282.05034 3755.65611) (11293.36256 3748.11505)))
("SF_ARCHITECTURE" 0 ((11282.05034 3755.65611) (11283.24898 3763.20407) (11293.36256 3774.50939)))
("SF_ARCHITECTURE" 0 ((11282.05034 3721.71946) (11282.05034 3733.03167)))
("SF_ARCHITECTURE" 0 ((11282.05034 3733.03167) (11292.15916 3740.57274) (11293.36256 3748.11505)))
("SF_SOLAR" 0 ((11293.36256 7963.80090) (11285.82296 7982.65452)))
("SF_ARCHITECTURE" 0 ((11289.59276 4407.99355) (11602.56369 4407.99355)))
("SF_ARCHITECTURE" 0 ((11289.59276 4407.99355) (11282.05124 4430.61799) (11282.05124 5188.53654) (11297.13518
5202.56324) (11331.07183 5203.47183) (11414.02715 5179.94570) (11493.21267 5142.23224) (11534.69174 5115.84287)
(11583.71041 5075.41437)))
("SF_SOLAR" 0 ((11292.10667 8058.06946) (11508.29468 8058.06946)))
("SF_ARCHITECTURE" 0 ((11304.67477 3763.19717) (11293.36256 3774.50939)))
("SF_ARCHITECTURE" 0 ((11304.67477 3785.82161) (11293.36256 3778.28054) (11293.36256 3774.50939)))
("SF_ARCHITECTURE" 0 ((11304.67477 3763.19717) (11303.47138 3755.65611) (11293.36256 3748.11505)))
("SF_SOLAR" 0 ((11297.13518 8020.36199) (11297.13518 8009.04977)))
("SF_ARCHITECTURE" 0 ((11297.13518 942.68382) (11376.32070 942.83224) (11395.17251 946.45645) (11436.65158 946.30803)
(11451.73360 942.69072) (11813.72590 942.68382)))
("SF_SOLAR" 0 ((11319.75962 7971.34231) (11300.90498 7967.57172)))
("SF_ARCHITECTURE" 0 ((11315.98699 859.72851) (11315.98213 765.46097) (11312.21719 742.83654) (11315.98077 373.30317)
(11300.90498 343.13631)))
("SF_ARCHITECTURE" 0 ((11304.67477 316.74208) (11301.05271 309.19480) (11300.90498 286.57523)))
("SF_ARCHITECTURE" 0 ((11315.98699 3782.05170) (11304.67477 3785.82161)))
("SF_ARCHITECTURE" 0 ((11315.98699 3804.67613) (11305.87964 3797.12760) (11304.67477 3785.82161)))
("SF_ARCHITECTURE" 0 ((11304.67477 3763.19717) (11314.78360 3774.50317) (11315.98699 3782.05170)))
("SF_ARCHITECTURE" 0 ((11304.67568 2198.34061) (11304.67568 2205.88235)))
("SF_ARCHITECTURE" 0 ((11315.98699 2145.55079) (11304.67568 2156.86301) (11304.67568 2190.79276) (11304.67568
2198.34061)))
("SF_ARCHITECTURE" 0 ((11304.67568 2198.34061) (11315.99457 2201.96414) (11349.91878 2201.95724) (11365.00848
2187.02839)))
("SF_SOLAR" 0 ((11308.44740 8039.21561) (11308.44740 8046.75724)))
("SF_SOLAR" 0 ((11312.21719 8107.08891) (11319.76448 8103.46629) (11368.77828 8103.32489) (11425.33937 8109.66199)
(11444.19400 8103.46629) (11493.21267 8107.08235) (11519.60690 8103.31833)))
("SF_ARCHITECTURE" 0 ((11334.84163 999.24491) (11323.38167 1018.09265) (11312.21719 1025.64197)))
("SF_ARCHITECTURE" 0 ((11334.84163 999.24491) (11323.52941 991.85860) (11304.67568 995.62975) (11304.67568 1018.09265)
(11312.21719 1025.64197)))
("SF_ARCHITECTURE" 0 ((11315.98699 2145.55079) (11312.22342 2096.53066) (11312.22342 1874.05758) (11315.83993
1858.97410) (11315.98699 1809.95475) (11312.22342 1787.33032) (11312.21719 1025.64197)))
("SF_SOLAR" 0 ((11315.98699 8005.27896) (11315.98699 8016.59118)))
("SF_SOLAR" 0 ((11315.98699 7986.42534) (11315.98699 7975.11312) (11319.75962 7971.34231)))
("SF_SOLAR" 0 ((11315.98699 7941.17647) (11315.98699 7933.63495)))
("SF_ARCHITECTURE" 0 ((11315.98699 3804.67613) (11323.52941 3800.90498)))
("SF_ARCHITECTURE" 0 ((11315.98699 3804.67613) (11317.19186 3812.22342) (11327.29921 3823.52941)))
("SF_ARCHITECTURE" 0 ((11323.52941 3800.90498) (11322.33145 3789.59898) (11315.98699 3782.05170)))
("SF_ARCHITECTURE" 0 ((11315.98699 2145.55079) (11331.21889 2171.79106) (11349.92364 2176.77262) (11365.00848
2187.02839)))
("SF_ARCHITECTURE" 0 ((11315.98699 859.72851) (11305.87964 867.27579) (11304.83009 878.58314) (11308.60068 886.11787)
(11319.75962 893.66516)))
("SF_ARCHITECTURE" 0 ((11315.98699 859.72851) (11327.30011 871.04072) (11319.75962 893.66516)))
("SF_SOLAR" 0 ((11327.29921 8080.69389) (11319.75962 8069.38167)))
("SF_SOLAR" 0 ((11319.75962 7971.34231) (11338.61143 7971.34231)))
("SF_ARCHITECTURE" 0 ((11319.75962 893.66516) (11361.23586 901.20667) (11508.29468 901.20667) (11530.91912 901.20667)
(11610.10600 901.20667) (11628.95928 901.20667) (11764.70588 901.20667) (11809.95475 901.20667) (11821.11233 901.20667)
(11825.03122 886.12274) (11825.03122 414.78224) (11821.26697 365.76075) (11825.03812 350.67873)))
("SF_SOLAR" 0 ((11323.52941 8088.23529) (11417.79695 8088.23529)))
("SF_ARCHITECTURE" 0 ((11323.52941 3800.90498) (11333.63676 3808.45294) (11334.84163 3819.75826)))
("SF_SOLAR" 0 ((11549.77376 8141.02557) (11327.29921 8141.02557)))
("SF_ARCHITECTURE" 0 ((11327.29921 3823.52941) (11334.84163 3819.75826)))
("SF_ARCHITECTURE" 0 ((11327.29921 3823.52941) (11332.12059 3834.68699) (11338.61143 3838.61278)))
("SF_ARCHITECTURE" 0 ((11338.61143 2364.25339) (11327.29921 2364.25339)))
("SF_ARCHITECTURE" 0 ((11327.29921 2364.25339) (11327.44762 2405.73179) (11331.07183 2417.04400)))
("SF_ARCHITECTURE" 0 ((11402.71493 4664.40464) (11388.68167 4656.71448) (11348.87489 4596.53133) (11331.07183
4577.67681)))
("SF_ARCHITECTURE" 0 ((12051.28201 2096.53066) (12024.88688 2101.50600) (11960.78473 2156.71448) (11870.28699
2219.90939) (11794.87138 2265.16448) (11644.04265 2340.57952) (11485.67025 2393.36312) (11410.25735 2409.35452)
(11331.07183 2417.04400)))
("SF_SOLAR" 0 ((11334.84163 8167.42081) (11349.92364 8163.65656) (11557.31618 8163.65000)))
("SF_ARCHITECTURE" 0 ((11346.15385 3838.61278) (11344.94898 3827.30679) (11334.84163 3819.75826)))
("SF_ARCHITECTURE" 0 ((11825.03812 999.24491) (11334.84163 999.24491)))
("SF_SOLAR" 0 ((11338.61143 8035.44502) (11338.61143 8046.75724)))
("SF_SOLAR" 0 ((11338.61143 8020.36199) (11342.38405 8005.27896)))
("SF_SOLAR" 0 ((11338.61143 7971.34231) (11338.61143 7986.42534)))
("SF_SOLAR" 0 ((11429.10916 7971.34231) (11338.61143 7971.34231)))
("SF_ARCHITECTURE" 0 ((11346.15385 3838.61278) (11338.61143 3838.61278)))
("SF_ARCHITECTURE" 0 ((11357.46606 3857.46606) (11343.43971 3853.54095) (11338.61143 3838.61278)))
("SF_ARCHITECTURE" 0 ((11338.61143 2364.25339) (11346.15385 2364.25339)))
("SF_ARCHITECTURE" 0 ((11338.61143 2364.25339) (11342.38405 2356.71165) (11346.15385 2364.25339)))
("SF_SOLAR" 0 ((11342.38405 8133.48416) (11342.38405 8118.40113)))
("SF_ARCHITECTURE" 0 ((11346.15385 3838.61278) (11356.26120 3846.16007) (11357.46606 3857.46606)))
("SF_ARCHITECTURE" 0 ((11500.75509 2334.08722) (11383.86029 2360.33518) (11346.15385 2364.25339)))
("SF_SOLAR" 0 ((11361.23586 8080.69389) (11357.46606 8069.38167)))
("SF_SOLAR" 0 ((11361.23586 8020.36199) (11357.46606 8012.82059)))
("SF_ARCHITECTURE" 0 ((11444.19400 3981.90045) (11367.72195 3861.39118) (11357.46606 3857.46606)))
("SF_ARCHITECTURE" 0 ((11459.27602 2168.17523) (11365.00848 2187.02839)))
("SF_ARCHITECTURE" 0 ((11372.54808 343.13631) (11383.86029 346.90204) (11776.01810 346.90894)))
("SF_SOLAR" 0 ((11380.09050 7986.42534) (11380.09050 7978.88394)))
("SF_SOLAR" 0 ((11387.63292 8080.69389) (11383.86029 8069.38167)))
("SF_SOLAR" 0 ((11383.86029 8035.44502) (11383.86029 8046.75724)))
("SF_SOLAR" 0 ((11383.86029 8005.27896) (11383.86029 8020.36199)))
("SF_SOLAR" 0 ((11391.40271 8133.48416) (11391.40271 8122.17195) (11387.63292 8118.40113)))
("SF_ARCHITECTURE" 0 ((11395.17251 4728.50679) (11430.30781 4788.83213) (11440.42138 4796.38009)))
("SF_ARCHITECTURE" 0 ((11402.71493 4664.40464) (11402.71493 4649.32127)))
("SF_ARCHITECTURE" 0 ((11402.71493 4664.40464) (11410.25735 4679.48676)))
("SF_SOLAR" 0 ((11406.48473 8005.27896) (11406.48473 8020.36199)))
("SF_SOLAR" 0 ((11406.48473 7986.42534) (11406.48473 7978.88394)))
("SF_ARCHITECTURE" 0 ((11410.25735 4679.48676) (11406.48473 4690.79898)))
("SF_SOLAR" 0 ((11410.25735 8035.44502) (11414.02715 8042.98643)))
("SF_ARCHITECTURE" 0 ((11410.25735 4679.48676) (11436.50385 4705.88235) (11466.81844 4751.13122)))
("SF_SOLAR" 0 ((11417.79695 8088.23529) (11417.79695 8095.77670)))
("SF_SOLAR" 0 ((11504.52489 8088.23529) (11417.79695 8088.23529)))
("SF_SOLAR" 0 ((11417.79695 8088.23529) (11417.79695 8069.38167)))
("SF_SOLAR" 0 ((11425.33937 8133.48416) (11421.56957 8118.40113)))
("SF_SOLAR" 0 ((11429.10916 8005.27896) (11429.10916 8016.59118)))
("SF_SOLAR" 0 ((11429.10916 7971.34231) (11429.10916 7982.65452)))
("SF_SOLAR" 0 ((11447.96380 7967.57172) (11429.10916 7971.34231)))
("SF_ARCHITECTURE" 0 ((11429.10916 6444.19310) (11945.70136 6444.19310) (11964.55464 6444.19310)))
("SF_ARCHITECTURE" 0 ((11429.10916 6444.19310) (11431.98631 6478.12308) (11436.80000 6484.47342) (11451.73360
6489.29367) (11968.32579 6489.44186)))
("SF_SOLAR" 0 ((11440.42138 7922.32274) (11440.42138 7941.17647)))
("SF_ARCHITECTURE" 0 ((11440.42138 4796.38009) (11447.96380 4792.60894)))
("SF_ARCHITECTURE" 0 ((11440.42138 4796.38009) (11441.62624 4803.92805) (11451.73360 4815.23337)))
("SF_ARCHITECTURE" 0 ((11440.42138 478.88292) (11440.42138 773.00057)))
("SF_SOLAR" 0 ((11444.19400 8035.44502) (11444.19400 8042.98643)))
("SF_ARCHITECTURE" 0 ((11474.35803 810.70984) (11463.04581 795.78032) (11444.19400 788.08541)))
("SF_SOLAR" 0 ((11451.73360 8133.48416) (11451.73360 8118.40113)))
("SF_SOLAR" 0 ((11451.73360 8069.38167) (11451.73360 8080.69389)))
("SF_SOLAR" 0 ((11451.73360 8016.59118) (11451.73360 8001.50837)))
("SF_ARCHITECTURE" 0 ((11463.04581 4815.23337) (11451.73360 4815.23337)))
("SF_ARCHITECTURE" 0 ((11451.73360 4815.23337) (11456.55498 4830.16210) (11463.04581 4834.08790)))
("SF_ARCHITECTURE" 0 ((11493.21267 3322.02138) (11459.27602 3322.02138)))
("SF_ARCHITECTURE" 0 ((11500.75509 2145.55079) (11474.35803 2150.37760) (11459.27602 2168.17523)))
("SF_ARCHITECTURE" 0 ((11508.29468 2160.63348) (11500.74751 2168.02059) (11470.58824 2171.79106) (11459.27602
2168.17523)))
("SF_SOLAR" 0 ((11700.60373 7948.71799) (11508.29468 7948.72455) (11493.21267 7952.19265) (11478.13066 7948.73111)
(11463.04581 7952.48869)))
("SF_ARCHITECTURE" 0 ((11463.04581 4849.17002) (11463.04581 4834.08790)))
("SF_ARCHITECTURE" 0 ((11470.58824 4834.08790) (11463.04581 4834.08790)))
("SF_ARCHITECTURE" 0 ((11463.04581 4815.23337) (11463.04581 4807.69231)))
("SF_ARCHITECTURE" 0 ((11463.04581 4815.23337) (11469.39027 4822.78190) (11470.58824 4834.08790)))
("SF_ARCHITECTURE" 0 ((11470.58824 4834.08790) (11480.70328 4841.63518) (11523.37952 4909.50226)))
("SF_SOLAR" 0 ((11474.35803 8118.40113) (11474.35803 8129.71335)))
("SF_SOLAR" 0 ((11474.35803 8069.38167) (11474.35803 8080.69389)))
("SF_SOLAR" 0 ((11474.35803 8039.21561) (11474.35803 8046.75724)))
("SF_SOLAR" 0 ((11481.90045 7937.40577) (11474.35803 7926.09355)))
("SF_ARCHITECTURE" 0 ((11651.58371 810.70984) (11579.93925 810.56143) (11561.08597 806.93722) (11474.35803 810.70984)))
("SF_ARCHITECTURE" 0 ((11651.58371 810.70984) (11670.43699 818.10238) (11700.60373 818.09615) (11711.76131 806.93722)
(11710.71188 430.01889) (11704.36674 426.24774) (11429.10916 426.10068) (11415.08348 433.64163) (11410.26222 448.71889)
(11414.02025 475.11312) (11410.26222 497.73756) (11410.25735 746.60633) (11414.18179 803.16742) (11417.95226 810.70226)
(11429.10916 818.09615) (11451.73360 818.10238) (11474.35803 810.70984)))
("SF_ARCHITECTURE" 0 ((11485.67025 1297.13518) (11547.05962 1402.71493) (11568.62839 1421.56957)))
("SF_SOLAR" 0 ((11493.21267 7960.03020) (11509.34559 7986.41867) (11519.60690 7993.81210) (11719.45701 7993.96674)))
("SF_SOLAR" 0 ((11496.98247 8133.48416) (11500.75509 8118.40113)))
("SF_SOLAR" 0 ((11508.29468 7997.73756) (11500.75509 7997.73756)))
("SF_ARCHITECTURE" 0 ((11500.75509 2334.08722) (11508.44310 2320.20871) (11527.14932 2322.77500)))
("SF_ARCHITECTURE" 0 ((11500.75509 2334.08722) (11519.60204 2336.65430) (11527.14932 2322.77500)))
("SF_ARCHITECTURE" 0 ((11500.75509 2145.55079) (11508.30226 2139.20622) (11538.46154 2134.23857)))
("SF_ARCHITECTURE" 0 ((11500.75509 2145.55079) (11508.29468 2153.09174) (11508.29468 2160.63348)))
("SF_SOLAR" 0 ((11504.52489 8024.13281) (11515.83710 8020.36199)))
("SF_SOLAR" 0 ((11519.60690 8065.61086) (11508.29468 8058.06946)))
("SF_ARCHITECTURE" 0 ((11508.29468 2160.63348) (11542.22647 2155.65882) (11549.77376 2145.55079)))
("SF_SOLAR" 0 ((11519.60690 8065.61086) (11530.91912 8058.06946)))
("SF_SOLAR" 0 ((11549.77376 8141.02557) (11541.03416 8114.63054) (11520.80554 8076.92319) (11519.60690 8065.61086)))
("SF_SOLAR" 0 ((11519.60690 8001.50837) (11535.88201 8039.21561) (11586.28303 8125.94265) (11587.48156 8137.25498)))
("SF_ARCHITECTURE" 0 ((11534.69174 2322.77500) (11527.14932 2322.77500)))
("SF_ARCHITECTURE" 0 ((11564.85577 2307.69231) (11542.37975 2308.89649) (11534.69174 2322.77500)))
("SF_ARCHITECTURE" 0 ((11568.62839 2315.23405) (11557.31618 2326.39163) (11534.69174 2322.77500)))
("SF_ARCHITECTURE" 0 ((11538.46154 2134.23857) (11546.00882 2127.89400) (11576.16934 2122.92636)))
("SF_ARCHITECTURE" 0 ((11538.46154 2134.23857) (11538.46154 2138.00905) (11549.77376 2145.55079)))
("SF_ARCHITECTURE" 0 ((11585.59536 1546.00396) (11566.05441 1534.54333) (11538.46154 1489.44287)))
("SF_SOLAR" 0 ((11542.23133 8182.50385) (11542.23133 8174.96222)))
("SF_SOLAR" 0 ((11647.81256 8027.90339) (11621.41821 8024.13937) (11602.56369 8027.60735) (11591.25147 8024.28077)
(11542.23133 8024.13281)))
("SF_SOLAR" 0 ((11542.23133 7971.34231) (11542.23133 7982.65452)))
("SF_SOLAR" 0 ((11564.85577 7971.34231) (11542.23133 7971.34231)))
("SF_SOLAR" 0 ((11542.23133 7971.34231) (11538.46154 7967.57172) (11542.23133 7960.03020)))
("SF_SOLAR" 0 ((11549.77376 8141.02557) (11572.40509 8171.03688) (11587.48156 8174.80747) (11594.86799 8171.03688)
(11598.78688 8159.87941) (11597.58971 8148.56719) (11587.48156 8137.25498)))
("SF_ARCHITECTURE" 0 ((11549.77376 2145.55079) (11568.62081 2144.34661) (11576.16934 2134.23857)))
("SF_SOLAR" 0 ((11557.31618 8054.29864) (11613.87590 8054.44661) (11644.04265 8059.12568) (11654.15079 8065.75894)
(11670.43699 8103.31833)))
("SF_SOLAR" 0 ((11564.85577 8012.82059) (11564.85577 8001.50837)))
("SF_SOLAR" 0 ((11564.85577 7971.34231) (11564.85577 7982.65452)))
("SF_SOLAR" 0 ((11564.85577 7971.34231) (11589.36652 7971.34231)))
("SF_ARCHITECTURE" 0 ((11576.16934 3329.56233) (11572.39819 3322.02138) (11564.85577 3322.02138)))
("SF_ARCHITECTURE" 0 ((11564.85577 2307.69231) (11572.54593 2297.58428) (11598.79378 2296.38009)))
("SF_ARCHITECTURE" 0 ((11564.85577 2307.69231) (11568.62839 2315.23405)))
("SF_ARCHITECTURE" 0 ((11598.79378 2303.92183) (11591.24457 2314.02986) (11568.62839 2315.23405)))
("SF_ARCHITECTURE" 0 ((11576.16934 1417.79695) (11568.62839 1421.56957)))
("SF_ARCHITECTURE" 0 ((11568.62839 1421.56957) (11591.25147 1463.04581)))
("SF_ARCHITECTURE" 0 ((11576.16934 2134.23857) (11602.55679 2133.03439) (11610.10600 2122.92636)))
("SF_ARCHITECTURE" 0 ((11576.16934 2122.92636) (11576.16934 2134.23857)))
("SF_ARCHITECTURE" 0 ((11606.33484 2111.61414) (11587.48156 2112.67048) (11576.16934 2122.92636)))
("SF_SOLAR" 0 ((11579.93925 8182.50385) (11587.48156 8190.04525) (11587.48156 8197.58665)))
("SF_SOLAR" 0 ((11587.48156 8137.25498) (11579.93925 8144.79638)))
("SF_SOLAR" 0 ((11659.12477 8103.31833) (11636.50034 8099.54751) (11583.71041 8103.31833)))
("SF_SOLAR" 0 ((11583.71041 8035.44502) (11583.71041 8042.98643)))
("SF_ARCHITECTURE" 0 ((11606.33484 5064.10215) (11602.40894 5074.21052) (11583.71041 5075.41437)))
("SF_ARCHITECTURE" 0 ((11583.71041 5075.41437) (11588.53801 5060.48620) (11598.79378 5056.56109)))
("SF_ARCHITECTURE" 0 ((11585.59536 1546.00396) (11583.71041 1527.14932)))
("SF_ARCHITECTURE" 0 ((11585.59536 1546.00396) (11583.71041 1549.77376) (11591.25147 1553.54355)))
("SF_ARCHITECTURE" 0 ((11585.59536 1546.00396) (11591.25147 1553.54355)))
("SF_SOLAR" 0 ((11589.36652 7971.34231) (11587.48156 7960.03020)))
("SF_SOLAR" 0 ((11589.36652 7971.34231) (11602.56369 7971.34231)))
("SF_SOLAR" 0 ((11598.79378 7986.42534) (11589.36652 7971.34231)))
("SF_ARCHITECTURE" 0 ((11602.56369 1579.94061) (11592.45554 1564.85577) (11591.25147 1553.54355)))
("SF_ARCHITECTURE" 0 ((11591.25147 1481.90045) (11587.63631 1474.35317) (11591.25147 1463.04581)))
("SF_ARCHITECTURE" 0 ((11606.33484 1485.67025) (11605.13066 1474.35803) (11591.25147 1463.04581)))
("SF_ARCHITECTURE" 0 ((11598.79378 5056.56109) (11609.04966 5033.93665) (11610.10554 5018.85396) (11625.18812
5007.54106)))
("SF_ARCHITECTURE" 0 ((11606.33484 5064.10215) (11606.33484 5060.33224) (11598.79378 5056.56109)))
("SF_ARCHITECTURE" 0 ((11598.79378 2303.92183) (11621.41131 2302.71765) (11628.95928 2292.60962)))
("SF_ARCHITECTURE" 0 ((11598.79378 2303.92183) (11598.79378 2296.38009)))
("SF_ARCHITECTURE" 0 ((11628.95928 2285.06787) (11610.10600 2286.27206) (11598.79378 2296.38009)))
("SF_ARCHITECTURE" 0 ((11598.79378 1500.75509) (11598.79378 1493.21267) (11606.33484 1485.67025)))
("SF_ARCHITECTURE" 0 ((11625.18812 4615.38462) (11632.57579 4604.07240) (11632.87828 4555.05238) (11640.27149
4543.74016) (11632.73043 4506.03360) (11636.34559 4408.00045) (11632.57579 4401.65701) (11606.48948 4401.65011)
(11602.56369 4407.99355)))
("SF_ARCHITECTURE" 0 ((11625.18812 4615.38462) (11617.78790 4611.45950) (11610.10554 4596.53133) (11610.10554
4426.84808) (11602.56369 4407.99355)))
("SF_ARCHITECTURE" 0 ((11610.10600 1602.56505) (11599.99796 1587.48778) (11602.56369 1579.94061)))
("SF_ARCHITECTURE" 0 ((11617.64706 1602.56505) (11616.44287 1591.25283) (11602.56369 1579.94061)))
("SF_SOLAR" 0 ((11606.33484 8144.79638) (11621.41821 8141.03869) (11636.50034 8144.64186) (11651.58371 8141.32172)
(11662.89593 8144.64830) (11730.76923 8144.79627) (11749.62251 8141.17364) (11809.95475 8141.02557)))
("SF_SOLAR" 0 ((11621.41821 8092.00611) (11617.64706 8088.23529) (11606.33484 8088.23529)))
("SF_ARCHITECTURE" 0 ((11606.33484 5064.10215) (11617.64706 5060.17726) (11635.44389 5037.70781) (11640.27149
5018.85396) (11625.18812 5007.54106)))
("SF_ARCHITECTURE" 0 ((11606.33484 2111.61414) (11613.88281 2105.27036) (11632.73043 2104.07240)))
("SF_ARCHITECTURE" 0 ((11606.33484 2111.61414) (11610.10600 2122.92636)))
("SF_ARCHITECTURE" 0 ((11606.33484 1485.67025) (11617.49932 1493.21957) (11647.81256 1538.46154)))
("SF_SOLAR" 0 ((11610.10600 8163.65000) (11817.49581 8163.64344) (11828.80803 8159.87941)))
("SF_SOLAR" 0 ((11613.87590 8012.82059) (11610.10600 8001.50837)))
("SF_ARCHITECTURE" 0 ((11636.50034 2111.61414) (11628.95238 2121.72217) (11610.10600 2122.92636)))
("SF_ARCHITECTURE" 0 ((11610.10600 1602.56505) (11617.64706 1602.56505)))
("SF_ARCHITECTURE" 0 ((11610.10600 1602.56505) (11615.06753 1617.49242) (11621.41821 1621.41686)))
("SF_SOLAR" 0 ((11613.87590 7963.80090) (11625.18812 7982.65452)))
("SF_SOLAR" 0 ((11621.41821 8080.69389) (11617.64706 8073.15226)))
("SF_ARCHITECTURE" 0 ((11617.64706 1602.56505) (11627.75509 1606.48948) (11628.95928 1621.41686)))
("SF_ARCHITECTURE" 0 ((11621.41821 1621.41686) (11628.95928 1621.41686)))
("SF_ARCHITECTURE" 0 ((11621.41821 1621.41686) (11625.18812 1632.72907)))
("SF_ARCHITECTURE" 0 ((11625.18812 4615.38462) (11625.18812 5007.54106)))
("SF_ARCHITECTURE" 0 ((11628.95928 2292.60962) (11647.80566 2291.40543) (11655.35486 2277.52613)))
("SF_ARCHITECTURE" 0 ((11628.95928 2285.06787) (11628.95928 2292.60962)))
("SF_ARCHITECTURE" 0 ((11628.95928 2285.06787) (11640.27839 2273.91029) (11655.35486 2277.52613)))
("SF_ARCHITECTURE" 0 ((11640.27149 1640.27149) (11639.06731 1628.96550) (11628.95928 1621.41686)))
("SF_SOLAR" 0 ((11632.73043 8133.48416) (11632.73043 8118.40113)))
("SF_SOLAR" 0 ((11632.73043 8001.50837) (11632.73043 8009.04977)))
("SF_ARCHITECTURE" 0 ((11632.73043 2104.07240) (11636.65498 2093.96437) (11659.12477 2088.98971)))
("SF_ARCHITECTURE" 0 ((11636.50034 2111.61414) (11632.73043 2104.07240)))
("SF_ARCHITECTURE" 0 ((11632.73043 1647.81391) (11640.27149 1640.27149)))
("SF_SOLAR" 0 ((11644.04265 7971.34231) (11636.50034 7971.34231)))
("SF_ARCHITECTURE" 0 ((11636.50034 2111.61414) (11655.34796 2110.40995) (11662.89593 2100.30192)))
("SF_ARCHITECTURE" 0 ((11640.27149 1640.27149) (11651.43597 1647.81878) (11715.68586 1749.62387)))
("SF_SOLAR" 0 ((11726.99808 8046.75724) (11718.40068 8027.90351) (11704.37364 8016.74593) (11674.20814 8016.73937)
(11647.81256 8027.90339)))
("SF_SOLAR" 0 ((11647.81256 8027.90339) (11652.78088 8046.75057) (11662.89593 8054.15057) (11677.97930 8057.92138)
(11760.93473 8058.06946)))
("SF_SOLAR" 0 ((11655.35486 7971.34231) (11647.81256 7963.80090)))
("SF_ARCHITECTURE" 0 ((11651.58371 810.70984) (11660.16867 795.78032) (11666.66708 791.85520)))
("SF_SOLAR" 0 ((11655.35486 7971.34231) (11693.06143 7971.34231)))
("SF_SOLAR" 0 ((11655.35486 7971.34231) (11659.12477 7982.65452)))
("SF_ARCHITECTURE" 0 ((11681.74921 2269.98518) (11655.35486 2277.52613)))
("SF_ARCHITECTURE" 0 ((11659.12477 2088.98971) (11666.67398 2078.88156) (11681.74921 2077.67749)))
("SF_ARCHITECTURE" 0 ((11662.89593 2100.30192) (11659.12477 2088.98971)))
("SF_ARCHITECTURE" 0 ((11662.89593 2100.30192) (11677.97240 2099.09774) (11685.52036 2088.98971)))
("SF_SOLAR" 0 ((11787.33032 8107.08891) (11764.70588 8100.74525) (11742.08145 8103.31176) (11693.06143 8099.55407)
(11670.43699 8103.31833)))
("SF_SOLAR" 0 ((11670.43699 8103.31833) (11677.97930 8133.48416)))
("SF_ARCHITECTURE" 0 ((11783.55916 3276.77251) (11776.01120 3273.14898) (11704.37364 3273.00747) (11670.43699
3280.54299)))
("SF_ARCHITECTURE" 0 ((11677.97885 4355.20362) (11670.44389 4321.26697) (11670.43699 3280.54299)))
("SF_ARCHITECTURE" 0 ((11677.97930 5067.87330) (11677.97885 4370.28699) (11677.97885 4355.20362)))
("SF_SOLAR" 0 ((11677.97930 8024.13281) (11685.52036 8046.75724)))
("SF_ARCHITECTURE" 0 ((11677.97930 5067.87330) (11685.37262 5071.79842) (11693.06143 5086.72658)))
("SF_ARCHITECTURE" 0 ((11681.74921 2269.98518) (11700.45464 2268.78100) (11708.14480 2254.90170)))
("SF_ARCHITECTURE" 0 ((11681.74921 2269.98518) (11693.06833 2252.33541) (11708.14480 2254.90170)))
("SF_ARCHITECTURE" 0 ((11704.37364 2070.13575) (11685.67500 2071.33371) (11681.74921 2077.67749)))
("SF_ARCHITECTURE" 0 ((11685.52036 2088.98971) (11681.74921 2077.67749)))
("SF_ARCHITECTURE" 0 ((11760.93473 3220.21143) (11759.88518 3205.12794) (11744.65407 3167.42081) (11711.91595
3140.87738) (11685.52036 3110.85973)))
("SF_ARCHITECTURE" 0 ((11685.52036 2088.98971) (11700.59683 2087.78552) (11708.14480 2077.67749)))
("SF_ARCHITECTURE" 0 ((11689.29152 460.03111) (11689.28462 776.77319) (11685.52036 791.85520)))
("SF_SOLAR" 0 ((11700.60373 8084.46448) (11700.60373 8076.92308) (11693.06143 8069.38167)))
("SF_SOLAR" 0 ((11708.14480 7967.57172) (11704.37364 7971.34231) (11693.06143 7971.34231)))
("SF_SOLAR" 0 ((11693.06143 7971.34231) (11696.83258 7986.42534)))
("SF_SOLAR" 0 ((11700.60373 7922.32274) (11701.66018 7933.63507) (11746.90905 8024.13281) (11782.50962 8076.92308)
(11828.80803 8159.87941)))
("SF_SOLAR" 0 ((11704.37364 7895.92760) (11708.14480 7861.99095)))
("SF_ARCHITECTURE" 0 ((11704.37364 2070.13575) (11708.29943 2060.02771) (11723.22817 2058.82353)))
("SF_ARCHITECTURE" 0 ((11704.37364 2070.13575) (11708.14480 2077.67749)))
("SF_SOLAR" 0 ((11708.14480 8118.40113) (11719.45701 8133.48416)))
("SF_ARCHITECTURE" 0 ((11708.14480 2254.90170) (11745.69796 2242.39231) (11749.62251 2236.04853)))
("SF_ARCHITECTURE" 0 ((11726.99808 2066.36527) (11719.45011 2076.47330) (11708.14480 2077.67749)))
("SF_SOLAR" 0 ((11719.45701 8012.82059) (11726.99808 8012.82059)))
("SF_ARCHITECTURE" 0 ((11723.22817 2058.82353) (11730.77613 2048.71550) (11742.08145 2047.51131)))
("SF_ARCHITECTURE" 0 ((11723.22817 2058.82353) (11726.99808 2066.36527)))
("SF_SOLAR" 0 ((11726.99808 7960.03020) (11730.76923 7948.71799)))
("SF_ARCHITECTURE" 0 ((11745.85260 2055.05305) (11738.30475 2065.16109) (11726.99808 2066.36527)))
("SF_SOLAR" 0 ((11730.76923 8031.67421) (11738.31029 8027.90339)))
("SF_SOLAR" 0 ((11749.62251 7948.71799) (11739.36663 7941.16991) (11734.54038 7922.32274)))
("SF_ARCHITECTURE" 0 ((11734.54038 2228.50679) (11742.08145 2228.50679) (11749.62251 2236.04853)))
("SF_ARCHITECTURE" 0 ((11760.93473 2032.42862) (11746.00735 2037.25543) (11742.08145 2047.51131)))
("SF_ARCHITECTURE" 0 ((11745.85260 2055.05305) (11742.08145 2047.51131)))
("SF_SOLAR" 0 ((11745.85260 8133.48416) (11745.85260 8118.40113)))
("SF_SOLAR" 0 ((11753.39367 8080.69389) (11745.85260 8076.92308) (11745.85260 8069.38167)))
("SF_ARCHITECTURE" 0 ((11745.85260 2055.05305) (11760.92783 2052.17738) (11768.47704 2043.74084)))
("SF_SOLAR" 0 ((11749.62251 7948.71799) (11750.67885 7960.03020) (11852.48880 8133.48405) (11862.74468 8144.79638)))
("SF_SOLAR" 0 ((11749.62251 7948.71799) (11934.38914 7949.77421) (11944.64502 7956.40747) (11965.61097 7997.73756)
(11983.40916 8020.36199)))
("SF_ARCHITECTURE" 0 ((11772.24695 2224.73631) (11764.69898 2234.84434) (11749.62251 2236.04853)))
("SF_ARCHITECTURE" 0 ((11757.16482 2217.19457) (11768.32240 2218.39253) (11772.24695 2224.73631)))
("SF_ARCHITECTURE" 0 ((11760.93473 3220.21143) (11790.95238 3221.41550) (11797.58620 3231.52364) (11797.43835
3265.45339) (11783.55916 3276.77251)))
("SF_ARCHITECTURE" 0 ((11779.78925 2021.11640) (11764.86052 2025.93631) (11760.93473 2032.42862)))
("SF_ARCHITECTURE" 0 ((11768.47704 2043.74084) (11764.70588 2043.74084) (11760.93473 2032.42862)))
("SF_SOLAR" 0 ((11772.24695 8133.48416) (11768.47704 8118.40113)))
("SF_ARCHITECTURE" 0 ((11787.33032 2032.42862) (11779.78235 2042.53665) (11768.47704 2043.74084)))
("SF_ARCHITECTURE" 0 ((11772.24695 2224.73631) (11787.17568 2223.53213) (11791.10147 2213.42410)))
("SF_SOLAR" 0 ((11957.01357 7997.73756) (11938.16029 8001.50181) (11874.05690 7994.11482) (11779.78925 7993.96674)))
("SF_ARCHITECTURE" 0 ((11779.78925 2205.88235) (11787.33032 2205.88235) (11791.10147 2213.42410)))
("SF_ARCHITECTURE" 0 ((11843.89140 1862.74536) (11832.57919 1874.05758) (11832.57919 1972.09627) (11821.26007
1987.03122) (11783.71380 2013.71618) (11779.78925 2021.11640)))
("SF_ARCHITECTURE" 0 ((11787.33032 2032.42862) (11783.55916 2032.42862) (11779.78925 2021.11640)))
("SF_ARCHITECTURE" 0 ((11843.89140 1862.74536) (11858.97432 1877.82805) (11858.97432 1987.17975) (11817.49581
2020.05995) (11798.64253 2031.23066) (11787.33032 2032.42862)))
("SF_SOLAR" 0 ((11791.10147 7982.65452) (11791.10147 7975.11312)))
("SF_SOLAR" 0 ((11791.10147 7975.11312) (11806.18360 7971.34887) (11911.76471 7971.49706) (11919.29887 7975.26765)
(11926.84808 7986.42534)))
("SF_SOLAR" 0 ((11791.10147 7967.57172) (11791.10147 7975.11312)))
("SF_ARCHITECTURE" 0 ((11791.10147 2213.42410) (11806.03575 2212.21991) (11817.49581 2194.57014)))
("SF_SOLAR" 0 ((11798.64253 7877.07387) (11798.64253 7865.76165) (11794.87138 7861.99095)))
("SF_SOLAR" 0 ((11802.41369 8027.90339) (11983.40916 8028.05814) (11993.67195 8035.45158) (12006.03360 8058.06946)))
("SF_SOLAR" 0 ((11821.26697 8099.54751) (11809.95475 8107.08891)))
("SF_SOLAR" 0 ((11817.49581 8016.59118) (11813.72590 8005.27896)))
("SF_ARCHITECTURE" 0 ((11817.49581 2194.57014) (11825.03812 2190.79966) (11825.03812 2187.02839)))
("SF_ARCHITECTURE" 0 ((11817.49581 2194.57014) (11821.26697 2187.02839) (11825.03812 2187.02839)))
("SF_SOLAR" 0 ((11821.26697 8058.06946) (11900.45249 8061.84005) (11994.72138 8061.83348) (12006.03360 8058.06946)))
("SF_SOLAR" 0 ((11825.03812 7858.22025) (11832.57919 7895.92760)))
("SF_ARCHITECTURE" 0 ((11998.49129 188.53790) (12002.26244 282.80543) (12002.26244 301.66007) (12002.26244 388.38518)
(12002.26244 411.00962) (12002.26244 441.17647) (12002.26244 475.11312) (12002.26244 501.50735) (12002.26244 520.36199)
(12002.26244 550.52885) (12002.26244 1093.51527) (12002.26244 1116.13971) (12002.26244 1161.38857) (12002.26244
2058.82353) (11987.17907 2081.30023) (11923.07692 2126.84457) (11907.99355 2141.62489) (11889.14027 2150.37760)
(11840.12025 2185.82432) (11825.03812 2187.02839)))
("SF_ARCHITECTURE" 0 ((11840.12025 1074.66063) (11851.27771 1067.11335) (11858.97432 1059.57862) (11858.97432 995.48201)
(11858.97432 989.13756) (11843.89140 988.08111) (11825.03812 999.24491)))
("SF_ARCHITECTURE" 0 ((11840.12025 1074.66063) (11832.57919 1063.34842) (11832.57919 1018.09955) (11825.03812
999.24491)))
("SF_SOLAR" 0 ((11828.80803 8159.87941) (11851.43247 8171.18495) (11885.36912 8163.65656) (12062.59468 8163.65000)))
("SF_SOLAR" 0 ((11847.66256 8141.02557) (11840.12025 8144.79638) (11836.35034 8141.02557)))
("SF_SOLAR" 0 ((11836.35034 8046.75724) (11836.35034 8039.21561)))
("SF_ARCHITECTURE" 0 ((11840.12025 1074.66063) (11843.89140 1862.74536)))
("SF_SOLAR" 0 ((11964.55464 8088.23529) (11843.89140 8088.23529)))
("SF_SOLAR" 0 ((11987.17907 8110.85973) (11979.63111 8113.27817) (11964.55464 8104.52262) (11851.43247 8107.08891)))
("SF_ARCHITECTURE" 0 ((11858.97477 852.18609) (11855.19672 320.51188) (11851.58020 305.42986) (11851.43247 241.32636)))
("SF_ARCHITECTURE" 0 ((11855.20362 935.14423) (11858.82704 927.59491) (11858.97477 889.89536)))
("SF_SOLAR" 0 ((11862.74468 8197.58665) (11858.97477 8182.50385)))
("SF_SOLAR" 0 ((11858.97477 8069.38167) (11858.97477 8080.69389)))
("SF_SOLAR" 0 ((11858.97477 8005.27896) (11858.97477 8016.59118)))
("SF_SOLAR" 0 ((11862.74468 8144.79638) (11877.82805 8141.03213) (12047.50441 8140.87760) (12055.05238 8137.25498)))
("SF_SOLAR" 0 ((11866.51584 8159.87941) (11862.74468 8144.79638)))
("SF_SOLAR" 0 ((11874.05690 7978.88394) (11877.82805 7986.42534)))
("SF_SOLAR" 0 ((11911.76471 7884.61538) (11904.21674 7877.22851) (11874.05690 7877.07387)))
("SF_SOLAR" 0 ((11885.36912 8133.48416) (11881.59921 8129.71335) (11881.59921 8118.40113)))
("SF_SOLAR" 0 ((11885.36912 8046.75724) (11881.59921 8039.21561)))
("SF_SOLAR" 0 ((11881.59921 8009.04977) (11881.59921 8016.59118)))
("SF_SOLAR" 0 ((11904.22364 8069.38167) (11904.22364 8080.69389)))
("SF_SOLAR" 0 ((11904.22364 8009.04977) (11904.22364 8016.59118)))
("SF_SOLAR" 0 ((11926.84808 8133.48416) (11930.61799 8118.40113)))
("SF_SOLAR" 0 ((11926.84808 8069.38167) (11938.16029 8080.69389)))
("SF_SOLAR" 0 ((11926.84808 8050.52783) (11926.84808 8039.21561)))
("SF_SOLAR" 0 ((12058.82353 7846.90803) (12024.88688 7843.13722) (11960.78473 7843.28529) (11938.16029 7846.90803)))
("SF_SOLAR" 0 ((11945.70136 8122.17195) (11949.47251 8129.71335)))
("SF_SOLAR" 0 ((11945.70136 8012.82059) (11949.47251 8020.36199)))
("SF_SOLAR" 0 ((11945.70136 7944.94717) (11960.78473 7937.40577)))
("SF_PLANTING" 0 ((11949.47251 6892.91075) (11983.40916 6918.24966) (12021.11572 6923.07692)))
("SF_ARCHITECTURE" 0 ((11998.49129 188.53790) (11983.40916 184.76527) (11960.79163 184.91369) (11953.24242 188.53790)))
("SF_ARCHITECTURE" 0 ((11953.24242 188.53790) (11960.78428 414.78224)))
("SF_ARCHITECTURE" 0 ((11960.78428 542.98643) (11960.78428 509.04977)))
("SF_SOLAR" 0 ((11960.78473 7960.03020) (11968.32579 7956.25939) (11968.32579 7952.48869)))
("SF_SOLAR" 0 ((11960.78473 7914.78133) (12131.51753 8174.96222) (12153.09796 8201.35090) (12168.17455 8212.66968)))
("SF_PLANTING" 0 ((12126.69683 6779.78857) (12107.84355 6783.55328) (11968.32579 6783.55984)))
("SF_PLANTING" 0 ((12006.03360 6557.31527) (12009.80351 6583.71041) (12006.04050 6606.33484) (12005.87896 6719.45701)
(12002.10781 6726.84389) (11976.92319 6742.08801) (11968.47353 6764.70588) (11968.32579 6783.55984)))
("SF_PLANTING" 0 ((12030.54299 6868.40147) (12013.57466 6852.63744) (11998.49129 6848.71176) (11930.61799 6847.51403)
(11916.74695 6839.97262) (11930.77262 6791.25566) (11949.47251 6783.70769) (11968.32579 6783.55984)))
("SF_SOLAR" 0 ((12024.88688 8103.31833) (11979.63801 8103.31833)))
("SF_SOLAR" 0 ((11990.95023 8125.94276) (11994.72138 8133.48416)))
("SF_SOLAR" 0 ((11994.72138 8084.46448) (11994.72138 8076.92308)))
("SF_PLANTING" 0 ((12030.54299 6868.40147) (12013.57466 6884.16516) (11994.72138 6885.36980)))
("SF_ARCHITECTURE" 0 ((12051.28247 188.53790) (12036.19910 184.76527) (11998.49129 188.53790)))
("SF_SOLAR" 0 ((12055.05238 8137.25498) (12023.83744 8076.92308) (12006.03360 8058.06946)))
("SF_PLANTING" 0 ((12006.03360 6557.31527) (12007.23778 6485.67783) (12013.58156 6479.33405) (12032.42794 6478.12964)))
("SF_SOLAR" 0 ((12017.34581 8133.48416) (12013.57466 8122.17195)))
("SF_SOLAR" 0 ((12013.57466 7873.30317) (12024.88688 7873.30317)))
("SF_SOLAR" 0 ((12021.11572 7990.19615) (12038.92081 7960.03020) (12050.23303 7926.09355) (12055.20011 7884.61538)
(12063.79197 7854.45600) (12088.98903 7839.36652)))
("SF_PLANTING" 0 ((12030.54299 6868.40147) (12046.83054 6844.25995) (12058.82081 6844.03620) (12130.46799 6860.17183)
(12149.32127 6877.82805)))
("SF_PLANTING" 0 ((12030.54299 6868.40147) (12055.05238 6884.46131) (12115.37771 6909.19174) (12126.69683 6923.07692)))
("SF_PLANTING" 0 ((12032.42794 6478.12964) (12032.43484 6202.86584) (12036.19219 6184.01199) (12039.97025 5829.56256)))
("SF_PLANTING" 0 ((12032.42794 6478.12964) (12055.05238 6481.89389) (12096.53133 6478.12964) (12119.15577 6481.89389)
(12247.36007 6481.90045)))
("SF_PLANTING" 0 ((12077.67681 6923.07692) (12039.97025 6923.07692)))
("SF_ARCHITECTURE" 0 ((12039.97025 5829.56256) (12043.74016 5810.70882) (12043.59231 5757.92511) (12039.97025
5750.37704)))
("SF_ARCHITECTURE" 0 ((12043.74061 5607.08857) (12043.74061 5625.94276) (12043.73326 5735.29412) (12039.97025
5750.37704)))
("SF_ARCHITECTURE" 0 ((12043.74061 5607.08857) (12043.74061 5592.00645) (12047.51131 4690.79898) (12047.51131
4668.17455) (12047.50441 4091.25147) (12043.74016 4068.62704) (12043.74706 3951.73495) (12047.50441 3914.02715)
(12043.74706 3887.63156) (12047.36357 3872.54943) (12047.51131 3797.13382)))
("SF_ARCHITECTURE" 0 ((12051.28247 3582.20238) (12029.86222 3597.28507) (12028.50339 3638.76278) (12014.62410
3665.15837) (12001.06527 3706.48213) (11979.64491 3718.09672) (11972.10385 3733.03167) (11972.25170 3782.05102)
(11976.02149 3789.43812) (11983.40916 3793.20894) (12036.19910 3793.51176) (12047.51131 3797.13382)))
("SF_ARCHITECTURE" 0 ((12428.35554 3797.13428) (12405.73111 3797.13428) (12371.79446 3797.13428) (12345.40011
3797.13428) (12066.36459 3797.13428) (12047.51131 3797.13382)))
("SF_MASONRY_AND_ARCH" 0 ((12051.28201 2820.51278) (12051.28201 2805.42986) (12051.28201 2714.93903) (12051.28201
2707.39038)))
("SF_MASONRY_AND_ARCH" 0 ((12051.28201 2820.51278) (12051.28201 2831.82477) (12051.28247 3582.20238)))
("SF_MASONRY_AND_ARCH" 0 ((12051.28201 2707.39038) (12051.28201 2692.30769) (12051.28201 2107.84287) (12051.28201
2096.53066)))
("SF_MASONRY_AND_ARCH" 0 ((12051.28247 188.53790) (12051.27557 346.90894) (12047.51131 369.53337) (12047.51821
531.67421) (12051.28247 554.29864) (12051.13473 633.48416) (12047.51131 652.33880) (12051.28201 1938.15962) (12051.28201
1953.24310) (12051.28201 2009.80419) (12051.28201 2047.51131) (12051.28201 2077.67749) (12051.28201 2096.53066)))
("SF_SOLAR" 0 ((12051.28247 8182.50385) (12051.28247 8174.96222)))
("SF_PLANTING" 0 ((12187.02907 6738.31097) (12085.21912 6738.30441) (12066.36459 6734.54627) (12051.28247 6738.31097)))
("SF_ARCHITECTURE" 0 ((13174.96188 3589.74333) (13159.87975 3585.97285) (12952.48869 3585.97907) (12929.86425
3589.74333) (12884.61538 3585.97907) (12846.90758 3589.74333) (12285.06787 3585.97285) (12266.21459 3585.97285)
(12171.94570 3585.97285) (12153.09242 3585.97285) (12141.78020 3585.97285) (12062.59468 3585.82511) (12051.28247
3582.20238)))
("SF_ARCHITECTURE" 0 ((12051.28247 188.53790) (12058.67579 165.91346) (12058.82353 120.66369)))
("SF_SOLAR" 0 ((12092.76018 8182.50385) (12055.05238 8137.25498)))
("SF_ARCHITECTURE" 0 ((12055.05238 3721.71946) (12066.36459 3717.95520) (13103.31867 3717.94208) (13118.40079
3714.17839)))
("SF_ARCHITECTURE" 0 ((12062.59468 67.87330) (12066.21674 75.42059) (12066.21674 109.35238) (12058.82353 120.66369)))
("SF_SOLAR" 0 ((12062.59468 7914.78133) (12070.13575 7914.78133)))
("SF_ARCHITECTURE" 0 ((12062.59468 67.87330) (12066.21674 56.56109) (12066.36459 -3.77070)))
("SF_ARCHITECTURE" 0 ((12134.23790 -3.77070) (12111.61346 -3.77070) (12066.36459 -3.77070)))
("SF_PLANTING" 0 ((12073.90690 6953.24310) (12048.56765 6972.09661) (12044.04253 6983.40848) (12051.28937 6993.51640)
(12062.59468 6994.57285) (12096.53133 6983.55679) (12122.92568 6982.35905) (12164.40464 6964.55532)))
("SF_SOLAR" 0 ((12077.67681 8020.36199) (12085.21912 8035.44502)))
("SF_ARCHITECTURE" 0 ((13122.17195 3650.07500) (12081.44796 3650.07500)))
("SF_SOLAR" 0 ((12092.76018 8084.46448) (12092.76018 8076.92308)))
("SF_ARCHITECTURE" 0 ((12100.30124 5833.33337) (12364.25339 5833.33337) (12386.87783 5833.33337) (12466.06335
5833.18507) (12481.14672 5829.56923) (12903.46867 5831.44796) (12922.32319 5831.44796) (12944.94762 5831.44796)
(12967.57206 5831.44796) (12990.19649 5831.44796) (13088.23529 5831.44796) (13099.54751 5831.44796)))
("SF_ARCHITECTURE" 0 ((12100.30124 5799.39661) (12153.09242 5799.24842) (12164.40464 5795.78077) (12198.34129
5799.39005) (12220.96572 5795.62602) (12383.10667 5795.63258) (12398.19005 5799.24186) (12417.03643 5795.78077)
(12424.58563 5799.39661)))
("SF_MASONRY_AND_ARCH" 0 ((12104.07240 3469.08020) (12122.92568 3472.84446) (12190.79898 3469.22794) (12202.11120
3472.70294) (12326.54559 3476.76889) (12341.62896 3480.38620) (12375.56561 3476.62115) (12450.97998 3476.76889)
(12466.06335 3480.38620) (12518.85328 3480.24468) (12537.70781 3476.62115) (12609.35102 3476.76889) (12624.43439
3480.38620) (12688.53654 3476.62805) (12711.16097 3480.38620) (12850.67873 3480.38552) (12903.46867 3472.85690)
(13009.04977 3472.85690) (13107.08857 3480.09615) (13118.40079 3476.62115)))
("SF_MASONRY_AND_ARCH" 0 ((12122.92568 2032.42862) (12104.07240 2036.19910)))
("SF_MASONRY_AND_ARCH" 0 ((12179.48676 1983.40848) (12168.17455 1973.29423) (12104.07240 1960.78405)))
("SF_MASONRY_AND_ARCH" 0 ((12130.46799 1342.38405) (12104.07240 1346.15385)))
("SF_PLANTING" 0 ((12104.07240 444.94627) (12104.07240 452.48869)))
("SF_MASONRY_AND_ARCH" 0 ((12217.19457 2907.23982) (12209.64661 2903.61708) (12130.46799 2903.31471) (12107.84355
2899.69808)))
("SF_MASONRY_AND_ARCH" 0 ((12107.84355 2752.63925) (12119.15577 2756.40430) (12145.55011 2752.65238) (12164.40464
2756.40430) (12311.46346 2756.55826) (12322.77568 2760.18100)))
("SF_MASONRY_AND_ARCH" 0 ((12107.84355 2658.37104) (12115.39152 2650.98394) (12134.23790 2650.82930)))
("SF_MASONRY_AND_ARCH" 0 ((12428.35554 2586.72726) (12405.73111 2579.33326) (12281.29672 2576.61290) (12187.02907
2579.33394) (12149.32127 2590.35000) (12115.39152 2590.35000) (12107.84355 2586.72726)))
("SF_MASONRY_AND_ARCH" 0 ((12107.84355 2386.87783) (12122.92568 2390.64830) (12202.11120 2390.50057) (12217.19457
2386.87783)))
("SF_MASONRY_AND_ARCH" 0 ((12107.84355 2247.36075) (12269.98450 2247.35452) (12322.77568 2239.81900) (12405.72421
2239.97364) (12413.27342 2247.36075)))
("SF_MASONRY_AND_ARCH" 0 ((12119.15577 1644.04129) (12107.84355 1644.04129)))
("SF_MASONRY_AND_ARCH" 0 ((12209.65351 1425.33937) (12194.57014 1429.10430) (12149.32127 1425.49400) (12115.39152
1429.26448) (12107.84355 1436.65158)))
("SF_MASONRY_AND_ARCH" 0 ((12126.69683 1244.34389) (12107.84355 1240.57410)))
("SF_MASONRY_AND_ARCH" 0 ((12315.23337 1180.24038) (12273.75566 1183.99921) (12258.67229 1180.38880) (12187.02907
1178.56957) (12111.76810 1182.81437) (12107.84355 1176.47059)))
("SF_MASONRY_AND_ARCH" 0 ((12107.84355 953.99604) (12119.15577 957.76176) (12236.04785 957.76867)))
("SF_PLANTING" 0 ((12107.84355 791.85520) (12153.09242 788.08541) (12269.98450 791.84898) (12285.06787 788.08541)))
("SF_PLANTING" 0 ((12107.84355 727.75170) (12149.32127 723.98190)))
("SF_MASONRY_AND_ARCH" 0 ((12319.00452 3273.00124) (12292.60894 3265.46652) (12266.21459 3269.22455) (12190.79898
3269.08303) (12179.48676 3265.75645) (12126.69683 3269.23077) (12111.61346 3265.46029)))
("SF_MASONRY_AND_ARCH" 0 ((12175.71686 3193.81572) (12111.61346 3186.27477)))
("SF_MASONRY_AND_ARCH" 0 ((12187.02907 3042.98643) (12168.17455 3046.74378) (12153.09242 3043.13416) (12111.61346
3042.98643)))
("SF_MASONRY_AND_ARCH" 0 ((12232.27794 2997.73756) (12217.04683 2975.26776) (12209.65351 2971.49729) (12171.94570
2974.81697) (12122.92568 2967.72602) (12111.61346 2971.34265)))
("SF_MASONRY_AND_ARCH" 0 ((12326.54559 2507.54174) (12288.83903 2502.09898) (12111.61346 2503.77048)))
("SF_MASONRY_AND_ARCH" 0 ((12138.00905 2303.92183) (12119.30362 2302.71765) (12111.61346 2288.83835)))
("SF_MASONRY_AND_ARCH" 0 ((12432.12670 1907.99423) (12379.33676 1904.22986) (12356.71233 1907.98801) (12239.81900
1907.98801) (12217.19457 1904.22296) (12111.61346 1907.99423)))
("SF_MASONRY_AND_ARCH" 0 ((12111.61346 1738.31165) (12149.32127 1735.73767) (12190.79898 1738.45871) (12213.42342
1745.70419) (12251.13122 1745.85124)))
("SF_MASONRY_AND_ARCH" 0 ((12111.61346 1595.02262) (12175.71686 1591.25283) (12217.19457 1594.87489) (12266.21459
1587.77715) (12292.60894 1594.87489) (12379.33676 1595.02885) (12398.19005 1598.77998) (12424.58563 1595.02262)))
("SF_MASONRY_AND_ARCH" 0 ((12111.61346 1033.18156) (12119.16267 1029.70792) (12134.23790 1033.17670) (12236.04785
1033.17670) (12258.67229 1029.41867) (12315.23337 1036.95419)))
("SF_PLANTING" 0 ((12122.92568 588.23529) (12111.61346 584.46550)))
("SF_PLANTING" 0 ((12126.69683 6923.07692) (12125.49265 6930.62523) (12115.38462 6941.93088)))
("SF_PLANTING" 0 ((12126.69683 6779.78857) (12122.92568 6760.93541)))
("SF_PLANTING" 0 ((12190.79898 6938.15962) (12183.11018 6927.89729) (12168.17455 6919.46086) (12126.69683 6923.07692)))
("SF_PLANTING" 0 ((12145.55011 6783.55984) (12126.69683 6779.78857)))
("SF_MASONRY_AND_ARCH" 0 ((12307.69231 1244.34389) (12164.40464 1244.33767) (12149.32127 1240.72738) (12126.69683
1244.34389)))
("SF_MASONRY_AND_ARCH" 0 ((12126.69683 1244.34389) (12124.27195 1274.35543) (12130.46799 1278.28054)))
("SF_PLANTING" 0 ((12126.69683 324.28450) (12164.40464 311.92206) (12202.11120 280.09129) (12217.19457 275.26301)))
("SF_SOLAR" 0 ((12130.46799 7843.13722) (12138.00905 7843.13722)))
("SF_MASONRY_AND_ARCH" 0 ((12130.46799 1342.38405) (12130.46799 1323.52941)))
("SF_MASONRY_AND_ARCH" 0 ((12718.70328 1346.15385) (12707.39106 1349.62817) (12658.37104 1346.16007) (12635.74661
1349.92364) (12613.12217 1346.16007) (12413.27342 1346.15385) (12405.73111 1346.15385) (12273.75566 1346.16007)
(12247.36007 1349.92364) (12239.81900 1349.92364) (12130.46799 1342.38405)))
("SF_SOLAR" 0 ((12149.32127 7869.53247) (12134.23790 7873.30317)))
("SF_PLANTING" 0 ((12134.23790 6832.57919) (12141.78020 6828.80871)))
("SF_MASONRY_AND_ARCH" 0 ((12134.23790 2714.93213) (12134.23790 2722.47387)))
("SF_MASONRY_AND_ARCH" 0 ((12430.24174 2630.09050) (12356.71233 2631.96991) (12341.62896 2628.35260) (12288.83903
2628.21109) (12243.59016 2631.96991) (12228.50679 2628.50113) (12202.11120 2631.96991) (12179.48676 2626.53337)
(12149.32817 2628.35950) (12142.83665 2632.13077) (12134.23790 2650.82930)))
("SF_MASONRY_AND_ARCH" 0 ((12138.00905 2669.68326) (12134.23790 2650.82930)))
("SF_MASONRY_AND_ARCH" 0 ((12141.78020 2032.42862) (12134.23790 2032.42862)))
("SF_ARCHITECTURE" 0 ((12134.23790 -3.77070) (12134.23790 184.76527)))
("SF_PLANTING" 0 ((12236.04785 245.09898) (12217.19457 233.94005) (12153.09242 233.63835) (12130.46799 228.81075)
(12116.58880 214.93213) (12115.54615 207.38971) (12134.23790 184.76527)))
("SF_ARCHITECTURE" 0 ((12134.23790 184.76527) (12156.86233 188.53790) (12179.48676 184.77217) (16097.28507 184.76527)
(16123.68213 180.99548) (16191.55543 181.14321) (16206.63462 184.76041) (17153.09389 184.76527) (17171.94570
180.99548)))
("SF_ARCHITECTURE" 0 ((12134.23790 -3.77070) (12153.09242 -3.77070) (17149.32127 -3.77070) (17168.17308 -3.77070)))
("SF_MASONRY_AND_ARCH" 0 ((12153.09242 2292.60962) (12138.00905 2303.92183)))
("SF_MASONRY_AND_ARCH" 0 ((12254.90238 2315.23405) (12153.09242 2315.07941) (12138.00905 2303.92183)))
("SF_PLANTING" 0 ((12145.55011 6783.55984) (12141.78020 6828.80871)))
("SF_PLANTING" 0 ((12190.79898 6840.12093) (12141.78020 6828.80871)))
("SF_MASONRY_AND_ARCH" 0 ((12247.36007 1670.43835) (12164.40464 1666.51244) (12141.78020 1644.04129)))
("SF_PLANTING" 0 ((12145.55011 6783.55984) (12247.36007 6779.78857)))
("SF_ARCHITECTURE" 0 ((12183.25792 7775.26391) (12160.63348 7775.41855) (12149.32127 7779.03473)))
("SF_SOLAR" 0 ((12307.69231 7873.30317) (12296.38009 7869.68054) (12202.11120 7869.52590) (12157.01143 7864.55735)
(12149.46900 7850.67873) (12149.32127 7779.03473)))
("SF_PLANTING" 0 ((12236.04785 263.95079) (12243.43552 275.26301) (12243.44242 297.88744) (12216.14514 358.22115)
(12202.10566 377.07296) (12153.09242 422.32183)))
("SF_ARCHITECTURE" 0 ((12156.86233 7631.97590) (12158.06640 7605.58066) (12175.71686 7579.18552)))
("SF_ARCHITECTURE" 0 ((12183.25792 7639.51731) (12156.86233 7631.97590)))
("SF_SOLAR" 0 ((12164.40464 8227.75271) (12160.63348 8223.98190) (12168.17455 8212.66968)))
("SF_PLANTING" 0 ((12217.19457 275.26301) (12219.76165 290.34785) (12201.05475 320.51188) (12164.40464 365.76075)))
("SF_SOLAR" 0 ((12171.94570 8201.35747) (12168.17455 8212.66968)))
("SF_ARCHITECTURE" 0 ((12175.71686 7579.18552) (12187.02862 7579.18552)))
("SF_MASONRY_AND_ARCH" 0 ((12175.71686 3386.12342) (12254.90238 3386.12342)))
("SF_MASONRY_AND_ARCH" 0 ((12481.14672 3193.81572) (12439.66776 3190.05147) (12330.31674 3189.89751) (12285.06787
3183.70147) (12175.71686 3193.81572)))
("SF_MASONRY_AND_ARCH" 0 ((12179.48676 3212.66968) (12175.71686 3193.81572)))
("SF_MASONRY_AND_ARCH" 0 ((12175.71686 2032.42862) (12183.25792 2028.65735)))
("SF_PLANTING" 0 ((12194.57014 554.29864) (12185.82500 580.54581) (12175.71686 588.23529)))
("SF_ARCHITECTURE" 0 ((12183.25792 7775.26391) (12567.87330 7775.26391)))
("SF_ARCHITECTURE" 0 ((12183.25792 7639.51731) (12183.25792 7775.26391)))
("SF_ARCHITECTURE" 0 ((12183.25792 7639.51731) (12194.57014 7635.75317) (12567.87330 7635.74661)))
("SF_MASONRY_AND_ARCH" 0 ((12183.25792 2028.65735) (12183.25792 2021.11640)))
("SF_MASONRY_AND_ARCH" 0 ((12183.25792 2028.65735) (12205.88235 2043.74084)))
("SF_ARCHITECTURE" 0 ((12187.02907 7068.25011) (12187.02862 7560.33179) (12187.02862 7579.18552)))
("SF_ARCHITECTURE" 0 ((12567.87330 7582.95622) (12549.02002 7586.72704) (12205.88235 7586.72704) (12187.02862
7579.18552)))
("SF_PLANTING" 0 ((12285.06787 7013.57466) (12266.21459 7018.54287) (12217.19457 7061.39649) (12187.02907 7068.25011)))
("SF_PLANTING" 0 ((12187.02907 7068.25011) (12190.79898 7032.42862)))
("SF_PLANTING" 0 ((12224.73563 6941.93088) (12214.47975 6957.01357) (12212.21923 6968.17093) (12190.94808 6976.02195)
(12174.66742 7002.26244) (12154.14197 7024.88688) (12130.62964 7073.89966) (12134.39253 7080.24344) (12141.78020
7081.29310) (12187.02907 7068.25011)))
("SF_PLANTING" 0 ((12187.02907 6960.78405) (12183.55486 6953.23620) (12190.79898 6938.15962)))
("SF_SOLAR" 0 ((12190.79898 7854.44943) (12190.79898 7846.90803)))
("SF_PLANTING" 0 ((12217.19457 6934.38914) (12190.79898 6938.15962)))
("SF_PLANTING" 0 ((12190.79898 6840.12093) (12209.65351 6832.72749) (12239.81900 6837.54740) (12249.93405 6847.66222)
(12254.90238 6862.74536)))
("SF_PLANTING" 0 ((12217.19457 6874.05758) (12198.49604 6862.73880) (12190.79898 6840.12093)))
("SF_MASONRY_AND_ARCH" 0 ((12417.04333 2092.76018) (12409.49536 2089.13744) (12341.62896 2086.41640) (12213.42342
2088.84118) (12198.34129 2081.44796)))
("SF_PLANTING" 0 ((12198.34129 727.75170) (12277.52681 727.75170)))
("SF_MASONRY_AND_ARCH" 0 ((12202.11120 2051.28179) (12205.88235 2043.74084)))
("SF_MASONRY_AND_ARCH" 0 ((12251.13122 3525.64129) (12205.88235 3525.64129)))
("SF_MASONRY_AND_ARCH" 0 ((12349.17002 2039.96957) (12337.85781 2043.73462) (12269.98450 2039.97647) (12254.90238
2043.59310) (12205.88235 2043.74084)))
("SF_PLANTING" 0 ((12209.65351 6738.31097) (12236.04785 6738.45882) (12254.90238 6745.85192)))
("SF_MASONRY_AND_ARCH" 0 ((12217.19457 2386.87783) (12215.99740 2368.03077) (12209.65351 2360.48292)))
("SF_PLANTING" 0 ((12220.96572 6998.49197) (12217.19457 7009.80419)))
("SF_PLANTING" 0 ((12217.19457 6990.95023) (12220.96572 6998.49197)))
("SF_PLANTING" 0 ((12217.19457 6874.05758) (12217.19457 6934.38914)))
("SF_PLANTING" 0 ((12224.73563 6941.93088) (12217.19457 6934.38914)))
("SF_PLANTING" 0 ((12217.19457 6874.05758) (12247.35317 6869.08880) (12254.90238 6862.74536)))
("SF_PLANTING" 0 ((12217.19457 6674.20814) (12220.96572 6681.74989)))
("SF_MASONRY_AND_ARCH" 0 ((12537.70781 3046.75690) (12447.21007 3046.75068) (12424.58563 3042.98643) (12322.77568
3042.99265) (12303.92115 3046.60226) (12232.27794 3040.41380) (12217.19457 3042.98643)))
("SF_MASONRY_AND_ARCH" 0 ((12217.19457 2907.23982) (12224.73563 2903.46934)))
("SF_MASONRY_AND_ARCH" 0 ((12217.19457 2907.23982) (12220.96572 2937.40600)))
("SF_MASONRY_AND_ARCH" 0 ((12217.19457 2386.87783) (12243.59016 2389.59197) (12253.70385 2382.95882) (12259.72862
2368.17851) (12266.22014 2364.40803) (12447.21007 2364.25962) (12469.83450 2368.01697) (12500.00000 2364.25962)
(12533.93665 2371.79514)))
("SF_PLANTING" 0 ((12217.19457 275.26301) (12236.04785 263.95079)))
("SF_PLANTING" 0 ((12220.96572 6998.49197) (12236.04785 6993.52319) (12253.84604 6975.86753) (12261.38710 6960.78405)
(12262.44344 6941.93088)))
("SF_PLANTING" 0 ((12220.96572 471.34333) (12238.76957 437.40667) (12268.92805 343.13631) (12274.95984 312.97229)
(12288.83903 301.66007)))
("SF_SOLAR" 0 ((12224.73563 7895.92760) (12262.44344 7895.92760)))
("SF_PLANTING" 0 ((12224.73563 6941.93088) (12247.36007 6941.77602) (12262.44344 6934.38914)))
("SF_PLANTING" 0 ((12228.50679 6595.02262) (12229.71097 6602.57093) (12239.81900 6613.87658)))
("SF_MASONRY_AND_ARCH" 0 ((12579.18552 1436.65158) (12560.33224 1432.88665) (12394.41889 1432.73337) (12375.56561
1427.43903) (12352.94118 1432.87489) (12232.27794 1429.10916)))
("SF_PLANTING" 0 ((12236.04785 263.95079) (12236.04785 245.09898)))
("SF_PLANTING" 0 ((12236.04785 245.09898) (12254.90238 237.70498) (12285.06097 237.70430) (12292.60894 241.32636)))
("SF_PLANTING" 0 ((12239.81900 6546.00328) (12229.71787 6538.45498) (12229.57002 6530.91980) (12236.19695 6519.75588)
(12247.36007 6512.06629)))
("SF_PLANTING" 0 ((12239.81900 588.23529) (12266.21459 592.00509)))
("SF_PLANTING" 0 ((12254.90238 6745.85192) (12254.74774 6764.70588) (12247.36007 6779.78857)))
("SF_PLANTING" 0 ((12247.36007 6779.78857) (12258.67229 6783.55984)))
("SF_PLANTING" 0 ((12247.36007 6512.06629) (12247.36007 6481.90045)))
("SF_PLANTING" 0 ((12273.75566 6546.00328) (12257.62274 6519.61448) (12247.36007 6512.06629)))
("SF_PLANTING" 0 ((12247.36007 6481.90045) (12330.31674 6481.90701) (12352.94118 6485.67127) (12371.79446 6481.90045)))
("SF_MASONRY_AND_ARCH" 0 ((12386.87783 1817.49717) (12296.38009 1817.50204) (12273.75566 1821.26697) (12247.36007
1817.49717)))
("SF_PLANTING" 0 ((12251.13122 6557.31550) (12262.44344 6561.08597)))
("SF_MASONRY_AND_ARCH" 0 ((12251.13122 957.76867) (12420.80758 957.61335) (12431.07036 946.45645) (12432.28133
912.51980) (12439.67466 902.41097) (12500.00000 901.20758)))
("SF_PLANTING" 0 ((12281.29672 6877.82805) (12269.98450 6867.57183) (12254.90238 6862.74536)))
("SF_PLANTING" 0 ((12288.83903 6738.31097) (12273.75566 6738.45882) (12254.90238 6745.85192)))
("SF_MASONRY_AND_ARCH" 0 ((12254.90238 2315.23405) (12266.21459 2305.12590) (12281.29672 2303.92183)))
("SF_MASONRY_AND_ARCH" 0 ((12258.67229 2326.54627) (12254.90238 2315.23405)))
("SF_PLANTING" 0 ((12258.67229 6783.55984) (12296.38009 6776.01810)))
("SF_PLANTING" 0 ((12262.44344 6794.87206) (12258.67229 6783.55984)))
("SF_MASONRY_AND_ARCH" 0 ((12405.73111 2899.69808) (12258.67229 2899.69808)))
("SF_PLANTING" 0 ((12258.67229 837.10407) (12259.87636 848.41629) (12273.75566 859.57387) (12307.69231 863.49344)
(12413.27342 863.50520) (12428.35554 866.97398) (12447.21007 863.50588) (12496.22885 867.27093)))
("SF_PLANTING" 0 ((12262.44344 6941.93088) (12315.23337 6933.19140) (12330.31674 6919.30645)))
("SF_PLANTING" 0 ((12262.44344 6934.38914) (12262.44344 6941.93088)))
("SF_PLANTING" 0 ((12281.29672 6877.82805) (12271.04084 6892.91075) (12269.83665 6911.76471) (12262.44344 6934.38914)))
("SF_PLANTING" 0 ((12262.44344 6561.08597) (12273.75566 6546.00328)))
("SF_PLANTING" 0 ((12262.44344 6561.08597) (12277.52681 6576.16867)))
("SF_MASONRY_AND_ARCH" 0 ((12269.98450 1466.81844) (12266.21459 1474.35803)))
("SF_PLANTING" 0 ((12269.98450 6659.12545) (12266.36934 6670.43767) (12271.04084 6681.74955) (12281.29118 6691.85781)
(12288.83903 6693.06210)))
("SF_PLANTING" 0 ((12281.29672 6610.10532) (12269.98450 6613.87658)))
("SF_MASONRY_AND_ARCH" 0 ((12424.58563 1534.69174) (12401.96120 1527.29706) (12281.29672 1526.99468) (12269.98450
1519.60690)))
("SF_PLANTING" 0 ((12273.75566 6546.00328) (12283.87070 6553.69253) (12287.63495 6564.84989) (12277.52681 6576.16867)))
("SF_PLANTING" 0 ((12281.29672 6610.10532) (12277.52681 6576.16867)))
("SF_MASONRY_AND_ARCH" 0 ((12296.38009 2417.04400) (12277.52681 2398.19005)))
("SF_PLANTING" 0 ((12281.29672 6877.82805) (12288.84593 6881.45068) (12311.46346 6881.59853)))
("SF_PLANTING" 0 ((12281.29672 6640.27149) (12292.60339 6643.74615) (12300.15124 6640.27149)))
("SF_PLANTING" 0 ((12281.29672 6610.10532) (12298.94717 6617.79536) (12300.15124 6640.27149)))
("SF_MASONRY_AND_ARCH" 0 ((12281.29672 3141.02590) (12277.52681 3144.79638) (12281.29672 3152.33812)))
("SF_MASONRY_AND_ARCH" 0 ((12458.52229 1749.62387) (12398.19005 1749.47545) (12379.33676 1745.85124) (12311.46346
1749.47545) (12292.60894 1739.50882) (12281.29672 1738.31165)))
("SF_PLANTING" 0 ((12285.06787 7013.57466) (12288.99378 7007.08281) (12322.77568 6987.03145) (12336.80136 6972.09627)
(12349.01527 6938.15962) (12341.62896 6919.30645)))
("SF_PLANTING" 0 ((12285.06787 7013.57466) (12292.76357 7038.92014) (12315.23337 7057.47115) (12330.31674 7053.86188)
(12345.39321 7043.59253) (12355.80373 7028.65735) (12380.39321 6957.16188) (12401.96120 6941.93088)))
("SF_MASONRY_AND_ARCH" 0 ((12285.06787 1666.66572) (12292.60894 1670.43835)))
("SF_PLANTING" 0 ((12285.06787 818.24943) (12285.06787 788.08541)))
("SF_PLANTING" 0 ((12526.39559 791.85520) (12518.84638 788.23247) (12420.81448 788.07851) (12401.96120 784.31968)
(12285.06787 788.08541)))
("SF_PLANTING" 0 ((12288.83903 6738.31097) (12296.38009 6738.31097)))
("SF_PLANTING" 0 ((12288.83903 6738.31097) (12288.83903 6693.06210)))
("SF_PLANTING" 0 ((12288.83903 6693.06210) (12303.92115 6681.74989)))
("SF_MASONRY_AND_ARCH" 0 ((12492.45894 3110.85973) (12443.43891 3110.71131) (12417.04333 3099.69593) (12311.46346
3102.12014) (12288.83903 3095.77704)))
("SF_MASONRY_AND_ARCH" 0 ((12288.83903 2473.60509) (12285.06787 2466.06335) (12288.83903 2462.29287)))
("SF_PLANTING" 0 ((12288.83903 301.66007) (12292.60894 241.32636)))
("SF_PLANTING" 0 ((12311.46346 335.59672) (12310.26493 324.28450) (12302.87161 312.97229) (12288.83903 301.66007)))
("SF_MASONRY_AND_ARCH" 0 ((12296.38009 1662.89593) (12292.60894 1670.43835)))
("SF_MASONRY_AND_ARCH" 0 ((12296.38009 1708.14480) (12299.99661 1681.75057) (12292.60894 1670.43835)))
("SF_PLANTING" 0 ((12379.33676 256.41120) (12368.01765 241.48167) (12349.17002 233.93382) (12319.00452 233.93382)
(12292.60894 241.32636)))
("SF_PLANTING" 0 ((12311.46346 6776.01810) (12296.38009 6776.01810)))
("SF_PLANTING" 0 ((12296.38009 6738.31097) (12296.38009 6776.01810)))
("SF_PLANTING" 0 ((12322.77568 6738.31097) (12296.38009 6738.31097)))
("SF_MASONRY_AND_ARCH" 0 ((12507.54106 2824.28382) (12386.87783 2824.27760) (12364.25339 2820.51256) (12296.38009
2824.28382)))
("SF_PLANTING" 0 ((12300.15124 6640.27149) (12319.00452 6647.66493) (12352.94118 6644.04197)))
("SF_PLANTING" 0 ((12303.92115 727.75170) (12315.22783 725.19299) (12330.31674 746.60633)))
("SF_SOLAR" 0 ((12307.69231 7873.30317) (12319.00452 7869.53247)))
("SF_SOLAR" 0 ((12307.69231 7873.30317) (12323.96606 7911.01052) (12508.59050 8193.81595) (12518.85328 8203.92398)
(12537.70781 8208.75090) (13190.04525 8212.66312) (13223.98190 8201.51199) (13246.60633 8208.75090) (13359.72851
8208.90543) (13378.58179 8212.66312) (13435.14287 8212.52172) (13450.22624 8208.90543) (13710.40724 8209.19491)
(13733.03167 8212.66968) (13774.50939 8208.90543) (13902.71493 8208.90543) (13925.33937 8212.66946) (13947.96380
8208.90543) (14042.23269 8208.89887)))
("SF_MASONRY_AND_ARCH" 0 ((12307.69231 1244.34389) (12307.69231 1217.94966)))
("SF_MASONRY_AND_ARCH" 0 ((12707.39106 1236.80147) (12594.26889 1234.22964) (12564.10215 1251.73100) (12500.00000
1252.03405) (12477.37557 1259.41968) (12447.21007 1252.03337) (12319.00452 1247.96663) (12307.69231 1244.34389)))
("SF_PLANTING" 0 ((12356.71233 6847.66188) (12334.09344 6855.35848) (12311.46346 6881.59853)))
("SF_PLANTING" 0 ((12311.46346 6881.59853) (12330.31674 6919.30645)))
("SF_PLANTING" 0 ((12322.77568 6772.24762) (12311.46346 6776.01810)))
("SF_PLANTING" 0 ((12330.31674 6817.49649) (12316.43190 6806.18394) (12311.46346 6776.01810)))
("SF_MASONRY_AND_ARCH" 0 ((12718.70328 2300.15057) (12699.84876 2303.92183) (12356.71233 2303.91561) (12311.46346
2300.15057)))
("SF_MASONRY_AND_ARCH" 0 ((12428.35554 1274.51075) (12394.41889 1285.67455) (12319.01143 1285.67455) (12311.46346
1282.05034)))
("SF_PLANTING" 0 ((12322.77568 456.25848) (12304.07025 448.57048) (12292.75667 422.32183) (12292.75667 395.92760)
(12300.30600 350.67873) (12311.46346 335.59672)))
("SF_PLANTING" 0 ((12337.85781 361.99095) (12326.39774 343.28473) (12311.46346 335.59672)))
("SF_PLANTING" 0 ((12315.23337 7115.38462) (12326.54559 7119.14197) (12337.70995 7115.22975) (12352.94118 7081.44796)))
("SF_MASONRY_AND_ARCH" 0 ((12315.23337 3389.89468) (12337.85781 3389.89468)))
("SF_MASONRY_AND_ARCH" 0 ((12315.23337 3389.89468) (12318.85679 3378.58247) (12319.00452 3337.10407)))
("SF_MASONRY_AND_ARCH" 0 ((12315.23337 3389.89468) (12319.00452 3423.83133)))
("SF_MASONRY_AND_ARCH" 0 ((12315.23337 1180.24038) (12311.61131 1134.99152) (12319.00452 1116.13971)))
("SF_MASONRY_AND_ARCH" 0 ((12315.23337 1180.24038) (12349.17002 1184.01210) (12394.41889 1184.01210) (12417.04333
1184.01210) (12533.93665 1184.01210)))
("SF_MASONRY_AND_ARCH" 0 ((12334.08790 1029.41176) (12315.23337 1036.95419)))
("SF_MASONRY_AND_ARCH" 0 ((12598.03880 1082.20305) (12515.08337 1082.19615) (12492.45894 1078.43043) (12345.40011
1082.05464) (12320.20871 1074.50600) (12315.23337 1036.95419)))
("SF_SOLAR" 0 ((12319.00452 7869.53247) (12319.00452 7877.07387)))
("SF_SOLAR" 0 ((13035.44536 7903.46912) (13027.89615 7903.46912) (13012.82093 7903.46912) (12556.56109 7903.32104)
(12541.47771 7898.50057) (12503.77115 7865.91629) (12341.62896 7865.76821) (12319.00452 7869.53247)))
("SF_MASONRY_AND_ARCH" 0 ((12319.00452 3306.93790) (12319.00452 3273.00124)))
("SF_MASONRY_AND_ARCH" 0 ((12541.47771 3257.91855) (12530.16550 3265.30566) (12435.89785 3262.88699) (12398.19005
3268.93462) (12330.31674 3269.37851) (12319.00452 3273.00124)))
("SF_PLANTING" 0 ((12319.00452 678.73303) (12319.00452 656.10860)))
("SF_PLANTING" 0 ((12322.77568 6772.24762) (12360.48224 6772.09932) (12375.56561 6764.70588)))
("SF_PLANTING" 0 ((12322.77568 6738.31097) (12322.77568 6772.24762)))
("SF_PLANTING" 0 ((12322.77568 6738.31097) (12345.40011 6715.68654)))
("SF_PLANTING" 0 ((12334.08790 6436.65158) (12322.77568 6432.88077)))
("SF_MASONRY_AND_ARCH" 0 ((12322.77568 2790.34717) (12322.77568 2760.18100)))
("SF_MASONRY_AND_ARCH" 0 ((12424.58563 2752.63925) (12417.03643 2756.26278) (12330.32364 2756.55826) (12322.77568
2760.18100)))
("SF_MASONRY_AND_ARCH" 0 ((12326.54559 2507.54174) (12326.39774 2545.24887) (12322.77568 2556.56109)))
("SF_PLANTING" 0 ((12322.77568 456.25848) (12326.54559 471.34333) (12322.77568 497.73756)))
("SF_PLANTING" 0 ((12322.77568 456.25848) (12351.88484 429.86425) (12360.33439 407.23982) (12360.48224 384.61538)))
("SF_MASONRY_AND_ARCH" 0 ((12575.41437 2496.22952) (12556.56109 2497.28586) (12533.93665 2507.39321) (12326.54559
2507.54174)))
("SF_PLANTING" 0 ((12326.54559 584.46550) (12326.54559 550.52885)))
("SF_PLANTING" 0 ((12341.62896 6919.30645) (12330.31674 6919.30645)))
("SF_PLANTING" 0 ((12345.40011 6715.68654) (12330.31674 6689.29084)))
("SF_MASONRY_AND_ARCH" 0 ((12334.08790 2209.65283) (12330.31674 2164.40396)))
("SF_SOLAR" 0 ((12530.16550 7903.46912) (12349.17002 7903.46256) (12334.08790 7899.69830)))
("SF_PLANTING" 0 ((12334.08790 6583.71041) (12334.08790 6591.25215)))
("SF_PLANTING" 0 ((12334.08790 6583.71041) (12337.85781 6576.16867)))
("SF_PLANTING" 0 ((12368.02455 6587.48088) (12334.08790 6583.71041)))
("SF_PLANTING" 0 ((12341.62896 6432.88077) (12334.08790 6436.65158)))
("SF_PLANTING" 0 ((12337.85781 6447.96380) (12334.08790 6436.65158)))
("SF_PLANTING" 0 ((12345.40011 6334.84163) (12334.23575 6319.75860) (12330.47138 6304.67579) (12334.08790 6293.36357)))
("SF_PLANTING" 0 ((12337.85781 361.99095) (12334.08790 380.84559)))
("SF_PLANTING" 0 ((12364.25339 6530.91980) (12345.40701 6529.72229) (12337.85781 6523.37885)))
("SF_PLANTING" 0 ((12337.85781 361.99095) (12356.71233 361.99095)))
("SF_PLANTING" 0 ((12341.62896 6919.30645) (12379.33676 6911.76471)))
("SF_PLANTING" 0 ((12356.71233 6847.66188) (12351.88484 6825.19231) (12341.62896 6821.26697)))
("SF_PLANTING" 0 ((12371.79446 6715.68654) (12345.40011 6715.68654)))
("SF_PLANTING" 0 ((12371.79446 6625.18880) (12356.86708 6632.87805) (12352.94118 6644.04197)))
("SF_PLANTING" 0 ((12371.79446 6655.35419) (12364.24649 6654.14989) (12352.94118 6644.04197)))
("SF_PLANTING" 0 ((12356.71233 6847.66188) (12383.10667 6851.43314)))
("SF_MASONRY_AND_ARCH" 0 ((12541.47771 3374.81120) (12536.65147 3408.74785) (12530.01765 3418.70758) (12420.81448
3416.29581) (12383.10667 3422.63337) (12356.71233 3420.06007)))
("SF_MASONRY_AND_ARCH" 0 ((12356.71233 2111.61414) (12368.02455 2115.38462)))
("SF_PLANTING" 0 ((12356.71233 361.99095) (12364.25339 339.36652)))
("SF_PLANTING" 0 ((12360.48224 384.61538) (12356.71233 361.99095)))
("SF_SOLAR" 0 ((12360.48224 7941.17647) (12375.56561 7937.40577)))
("SF_MASONRY_AND_ARCH" 0 ((12360.48224 1029.41176) (12375.56561 1033.02828) (12390.64898 1029.41176)))
("SF_PLANTING" 0 ((12360.48224 384.61538) (12383.10667 384.61538)))
("SF_PLANTING" 0 ((12364.25339 6530.91980) (12375.56561 6512.06629)))
("SF_PLANTING" 0 ((12375.56561 6579.93993) (12364.40803 6546.00328) (12364.25339 6530.91980)))
("SF_PLANTING" 0 ((12371.79446 297.88744) (12364.40113 312.97229) (12364.25339 339.36652)))
("SF_PLANTING" 0 ((12383.10667 384.61538) (12389.58575 361.99095) (12382.95882 350.82647) (12364.25339 339.36652)))
("SF_PLANTING" 0 ((12368.02455 6587.48088) (12375.56561 6579.93993)))
("SF_PLANTING" 0 ((12368.02455 6587.48088) (12371.79446 6625.18880)))
("SF_MASONRY_AND_ARCH" 0 ((12368.02455 1395.17251) (12375.56561 1391.40271)))
("SF_SOLAR" 0 ((12375.56561 7937.40577) (12375.56561 7926.09355) (12371.79446 7922.32274)))
("SF_PLANTING" 0 ((12371.79446 6655.35419) (12371.79446 6715.68654)))
("SF_PLANTING" 0 ((12371.79446 6715.68654) (12383.10667 6719.45701)))
("SF_PLANTING" 0 ((12371.79446 6655.35419) (12382.95192 6651.42885) (12386.87783 6636.50102)))
("SF_PLANTING" 0 ((12371.79446 6625.18880) (12386.87783 6636.50102)))
("SF_PLANTING" 0 ((12379.33676 6478.12964) (12371.79446 6481.90045)))
("SF_PLANTING" 0 ((12371.79446 6481.90045) (12375.56561 6512.06629)))
("SF_PLANTING" 0 ((12375.56561 6406.48575) (12371.80136 6372.54910) (12371.80136 6285.82195) (12375.56561 6263.19751)
(12371.80136 6221.71946) (12379.03439 6191.56018) (12371.79446 6184.01199)))
("SF_PLANTING" 0 ((12379.33676 256.41120) (12371.79446 297.88744)))
("SF_PLANTING" 0 ((12371.79446 297.88744) (12394.41335 313.11934) (12413.27896 338.16855) (12443.43891 350.83337)
(12457.32376 365.76075) (12462.29219 384.61538)))
("SF_SOLAR" 0 ((12386.87783 7941.17647) (12375.56561 7937.40577)))
("SF_PLANTING" 0 ((12386.87783 6734.53971) (12376.76980 6742.08801) (12375.56561 6764.70588)))
("SF_PLANTING" 0 ((12375.56561 6764.70588) (12386.73009 6802.41301) (12386.73009 6840.12059) (12383.10667 6851.43314)))
("SF_PLANTING" 0 ((12405.73111 6583.71041) (12375.56561 6579.93993)))
("SF_PLANTING" 0 ((12390.64898 6515.83710) (12379.33676 6515.83710) (12375.56561 6512.06629)))
("SF_PLANTING" 0 ((12386.87783 6858.97410) (12379.33676 6911.76471)))
("SF_PLANTING" 0 ((12379.33676 6911.76471) (12401.96120 6926.84740)))
("SF_PLANTING" 0 ((12379.33676 6478.12964) (12379.48462 6455.50520) (12384.30520 6440.57715) (12413.27342 6429.11018)))
("SF_PLANTING" 0 ((12379.33676 6478.12964) (12405.72421 6478.27771) (12413.27342 6481.90045)))
("SF_PLANTING" 0 ((12386.87783 686.27545) (12379.33676 686.27545)))
("SF_PLANTING" 0 ((12379.33676 256.41120) (12390.64898 256.41120)))
("SF_SOLAR" 0 ((12386.87783 7963.80090) (12383.10667 7971.34231)))
("SF_PLANTING" 0 ((12386.87783 6858.97410) (12383.10667 6851.43314)))
("SF_PLANTING" 0 ((12445.32387 6630.84491) (12425.64208 6651.58371) (12408.30509 6693.06210) (12383.10667 6719.45701)))
("SF_PLANTING" 0 ((12386.87783 6734.53971) (12386.87783 6723.22749) (12383.10667 6719.45701)))
("SF_MASONRY_AND_ARCH" 0 ((12383.10667 2043.74084) (12387.03247 2037.39706) (12503.76425 2040.11731) (12511.31222
2043.74084)))
("SF_PLANTING" 0 ((12398.19005 399.69740) (12383.10667 384.61538)))
("SF_SOLAR" 0 ((12386.87783 7941.17647) (12401.96120 7937.41233) (12432.12670 7941.16991) (12450.97998 7937.41233)
(12556.56109 7937.40577)))
("SF_SOLAR" 0 ((12386.87783 7941.17647) (12459.56493 8061.68541) (12466.06335 8065.61086)))
("SF_PLANTING" 0 ((12439.66776 6840.12093) (12435.74321 6847.52093) (12424.58563 6854.15419) (12398.19005 6861.54762)
(12386.87783 6858.97410)))
("SF_PLANTING" 0 ((12386.87783 6734.53971) (12409.35452 6753.39367) (12424.58563 6779.78857)))
("SF_PLANTING" 0 ((12445.32387 6630.84491) (12432.12941 6629.11063) (12413.27342 6636.35271) (12386.87783 6636.50102)))
("SF_PLANTING" 0 ((12390.64898 6515.83710) (12390.50124 6542.22545) (12386.87783 6549.77376)))
("SF_PLANTING" 0 ((12386.87783 686.27545) (12413.27342 685.21833) (12481.14672 642.22376) (12511.31222 628.65724)
(12556.41335 584.46550) (12582.95667 550.52885)))
("SF_PLANTING" 0 ((12386.87783 686.27545) (12391.69853 659.87839) (12405.73111 633.48416)))
("SF_PLANTING" 0 ((12409.50226 6512.06629) (12390.64898 6515.83710)))
("SF_PLANTING" 0 ((12390.64898 456.25848) (12401.96120 444.94627)))
("SF_PLANTING" 0 ((12469.83450 252.63857) (12439.66776 238.61290) (12413.27342 237.70498) (12398.19695 245.24604)
(12390.64898 256.41120)))
("SF_PLANTING" 0 ((12413.27342 286.57523) (12409.34762 275.26301) (12390.64898 256.41120)))
("SF_PLANTING" 0 ((12398.19005 399.69740) (12419.97907 393.42681) (12432.12398 395.77014) (12462.29219 384.61538)))
("SF_PLANTING" 0 ((12398.19005 399.69740) (12401.96120 444.94627)))
("SF_PLANTING" 0 ((12401.96120 6941.93088) (12401.96120 6926.84740)))
("SF_PLANTING" 0 ((12401.96120 6941.93088) (12413.27342 6994.72070)))
("SF_PLANTING" 0 ((12450.97998 6923.07692) (12401.96120 6926.84740)))
("SF_PLANTING" 0 ((12401.96120 444.94627) (12424.36471 448.93846) (12450.97998 524.13179)))
("SF_PLANTING" 0 ((12409.50226 6512.06629) (12423.38710 6530.91980) (12426.25656 6542.23201) (12419.90588 6561.08597)
(12405.73111 6583.71041)))
("SF_PLANTING" 0 ((12409.50226 6598.79310) (12405.73111 6583.71041)))
("SF_PLANTING" 0 ((12405.73111 633.48416) (12424.58563 628.65724) (12462.29219 588.38993) (12481.14672 580.69287)))
("SF_PLANTING" 0 ((12405.73111 633.48416) (12410.69943 603.31731) (12442.53032 554.29864) (12450.97998 524.13179)))
("SF_PLANTING" 0 ((12409.50226 6512.06629) (12413.12568 6504.51833) (12413.27342 6481.90045)))
("SF_SOLAR" 0 ((12413.27342 7918.55204) (12413.27342 7926.09355)))
("SF_PLANTING" 0 ((12413.27342 7096.53066) (12399.24638 7066.36527) (12396.51776 7051.28179) (12399.23948 7017.34514)
(12403.15848 7006.03326) (12413.27342 6994.72070)))
("SF_PLANTING" 0 ((12435.89785 6994.72070) (12413.27342 6994.72070)))
("SF_PLANTING" 0 ((12413.27342 6481.90045) (12522.62443 6481.90045)))
("SF_PLANTING" 0 ((12413.27342 6429.11018) (12414.47760 6417.79796) (12432.12670 6402.71493)))
("SF_PLANTING" 0 ((12413.27342 6429.11018) (12424.58563 6436.65158)))
("SF_PLANTING" 0 ((12417.04333 6293.36357) (12414.47760 6300.91154) (12420.66674 6323.52941) (12413.27342 6349.92466)))
("SF_SOLAR" 0 ((12420.81448 8016.59118) (12417.04333 8027.90339)))
("SF_SOLAR" 0 ((12575.41437 7971.34231) (12417.04333 7971.34231)))
("SF_MASONRY_AND_ARCH" 0 ((12417.04333 2899.69808) (12518.85328 2899.55034) (12541.47771 2892.15713)))
("SF_MASONRY_AND_ARCH" 0 ((12432.12670 2088.98971) (12417.04333 2092.76018)))
("SF_MASONRY_AND_ARCH" 0 ((12424.58563 2130.46731) (12417.19106 2111.61414) (12417.04333 2092.76018)))
("SF_MASONRY_AND_ARCH" 0 ((12417.04333 1817.49717) (12469.83450 1817.49717)))
("SF_PLANTING" 0 ((12420.81448 7111.61414) (12428.50464 7121.86991) (12439.66776 7126.39412) (12447.05543 7122.77127)
(12450.82523 7115.38462) (12450.83213 7088.98971) (12443.58665 7062.59400) (12435.89785 7002.26244)))
("SF_ARCHITECTURE" 0 ((12420.81448 5757.91855) (12424.58563 5769.23077)))
("SF_MASONRY_AND_ARCH" 0 ((12420.81448 1474.35803) (12420.81448 1504.52489)))
("SF_PLANTING" 0 ((12424.58563 6779.78857) (12473.60441 6779.78857)))
("SF_PLANTING" 0 ((12439.66776 6840.12093) (12425.64208 6813.72523) (12424.58563 6779.78857)))
("SF_PLANTING" 0 ((12424.58563 6455.50520) (12424.58563 6436.65158)))
("SF_PLANTING" 0 ((12424.58563 6436.65158) (12435.74321 6425.33281) (12432.12670 6402.71493)))
("SF_MASONRY_AND_ARCH" 0 ((12424.58563 2752.63925) (12428.35554 2711.16165)))
("SF_MASONRY_AND_ARCH" 0 ((12424.58563 2752.63925) (12439.66776 2760.03258) (12507.54106 2762.75362) (12533.93665
2760.18100)))
("SF_MASONRY_AND_ARCH" 0 ((12624.43439 2220.96505) (12575.41437 2213.43032) (12545.24887 2217.18767) (12518.85328
2213.42410) (12500.00000 2217.04683) (12432.13360 2217.03993) (12424.58563 2209.65283)))
("SF_MASONRY_AND_ARCH" 0 ((12432.12670 1530.91912) (12424.58563 1534.69174)))
("SF_MASONRY_AND_ARCH" 0 ((12424.58563 1534.69174) (12428.35554 1561.08597)))
("SF_SOLAR" 0 ((12428.35554 7960.03020) (12428.35554 7952.48869)))
("SF_ARCHITECTURE" 0 ((12948.71753 3797.13382) (12933.63541 3793.36391) (12439.66776 3797.13428) (12428.35554
3797.13428)))
("SF_ARCHITECTURE" 0 ((12477.37557 5701.35747) (12469.82760 5708.74412) (12443.43891 5708.75068) (12428.35600
5704.07195) (12428.35600 5693.81572) (12428.35554 3797.13428)))
("SF_MASONRY_AND_ARCH" 0 ((12430.24174 2630.09050) (12431.97896 2650.82930) (12428.35554 2662.14152)))
("SF_MASONRY_AND_ARCH" 0 ((12428.35554 2586.72726) (12443.43891 2583.10373) (12507.54106 2582.95600)))
("SF_MASONRY_AND_ARCH" 0 ((12428.35554 2586.72726) (12430.24174 2630.09050)))
("SF_MASONRY_AND_ARCH" 0 ((12435.89785 1036.95419) (12428.35554 1031.92568)))
("SF_PLANTING" 0 ((12484.91663 739.06391) (12469.83450 735.29412) (12428.35554 739.06391)))
("SF_MASONRY_AND_ARCH" 0 ((12430.24174 2630.09050) (12469.83450 2631.96991) (12522.62443 2628.21109) (12533.93665
2631.97613)))
("SF_SOLAR" 0 ((12432.12670 8137.25498) (12435.89785 8144.79638)))
("SF_PLANTING" 0 ((12435.89785 6395.17353) (12432.12670 6402.71493)))
("SF_MASONRY_AND_ARCH" 0 ((12432.12670 1907.99423) (12473.60441 1900.60713) (12492.45894 1904.21674) (12582.95667
1904.37070) (12594.26889 1907.83959) (12613.12217 1904.38462) (12623.23722 1911.77161) (12628.20554 1926.84740)))
("SF_MASONRY_AND_ARCH" 0 ((12435.89785 1923.07692) (12432.12670 1919.30645) (12432.12670 1907.99423)))
("SF_SOLAR" 0 ((12435.89785 8061.84005) (12439.66776 8054.29864)))
("SF_PLANTING" 0 ((12435.89785 6994.72070) (12435.89785 7002.26244)))
("SF_PLANTING" 0 ((12435.89785 7002.26244) (12473.60441 7021.11640)))
("SF_PLANTING" 0 ((12435.89785 6994.72070) (12448.41425 6960.79095) (12458.52229 6953.24310)))
("SF_MASONRY_AND_ARCH" 0 ((12435.89785 1874.05758) (12435.89785 1862.74536)))
("SF_MASONRY_AND_ARCH" 0 ((12435.89785 995.47511) (12447.21007 999.24005) (12628.19864 999.40023) (12635.59197
1006.79423) (12635.89434 1040.72398) (12639.51776 1052.03620)))
("SF_SOLAR" 0 ((12439.66776 8012.82059) (12601.80995 8012.81403) (12613.12217 8009.04977)))
("SF_PLANTING" 0 ((12439.66776 6840.12093) (12447.21007 6840.12093)))
("SF_ARCHITECTURE" 0 ((12443.43891 5799.39661) (12477.37557 5795.62602) (12956.25984 5795.63258) (12971.34197
5799.24186) (12986.42534 5795.92229) (12997.73756 5799.10034) (13009.04977 5795.77421) (13088.23529 5795.63258)
(13103.31867 5799.39661)))
("SF_PLANTING" 0 ((12445.32387 6630.84491) (12453.47930 6621.48518) (12455.95532 6602.56437) (12469.83450 6588.69174)
(12515.08337 6598.79310)))
("SF_PLANTING" 0 ((12445.32387 6630.84491) (12462.29219 6637.70498) (12481.14672 6654.14989) (12500.00000 6655.35419)))
("SF_SOLAR" 0 ((12450.97998 7997.73756) (12447.21007 7982.65452)))
("SF_PLANTING" 0 ((12473.60441 6779.78857) (12472.54796 6809.95475) (12447.21007 6840.12093)))
("SF_PLANTING" 0 ((12462.29219 6870.28631) (12447.21007 6840.12093)))
("SF_SOLAR" 0 ((12454.75113 8069.38167) (12450.97998 8084.46448)))
("SF_PLANTING" 0 ((12462.29219 6870.28631) (12450.97998 6923.07692)))
("SF_PLANTING" 0 ((12458.52229 6953.24310) (12457.47285 6938.15962) (12450.97998 6923.07692)))
("SF_PLANTING" 0 ((12537.70781 441.17647) (12537.55317 460.03111) (12533.78201 467.42364) (12515.08337 479.03133)
(12469.83450 519.16403) (12450.97998 524.13179)))
("SF_SOLAR" 0 ((12571.64446 8039.21561) (12473.60441 8039.22217) (12458.52229 8042.98643)))
("SF_SOLAR" 0 ((12458.52229 7997.73756) (12511.31222 7997.73756)))
("SF_PLANTING" 0 ((12458.52229 6953.24310) (12511.31222 6991.09853) (12526.39559 7009.80419)))
("SF_SOLAR" 0 ((12469.83450 8095.77670) (12462.29219 8099.54751)))
("SF_PLANTING" 0 ((12462.29219 6870.28631) (12481.14672 6870.28631)))
("SF_PLANTING" 0 ((12462.29219 384.61538) (12481.14672 384.61538)))
("SF_SOLAR" 0 ((12639.51776 8061.84005) (12477.37557 8061.84661) (12466.06335 8065.61086)))
("SF_SOLAR" 0 ((12530.16550 8163.65000) (12485.96606 8103.31833) (12466.06335 8065.61086)))
("SF_MASONRY_AND_ARCH" 0 ((12466.06335 2088.98971) (12473.61131 2086.41640) (12526.39559 2092.76018) (12560.33224
2088.98971)))
("SF_MASONRY_AND_ARCH" 0 ((12522.62443 1598.79242) (12477.38247 1598.64536) (12469.83450 1595.02262)))
("SF_MASONRY_AND_ARCH" 0 ((12469.83450 1564.85577) (12537.70781 1568.62839) (12733.78541 1564.86267) (12752.63993
1568.62149) (12858.21290 1568.77545) (12865.76210 1572.39819)))
("SF_PLANTING" 0 ((12469.83450 618.40215) (12481.14672 580.69287)))
("SF_PLANTING" 0 ((12469.83450 252.63857) (12469.83450 267.72342)))
("SF_PLANTING" 0 ((12469.83450 267.72342) (12469.98235 309.19480) (12473.60441 316.74208)))
("SF_PLANTING" 0 ((12511.31222 279.03563) (12469.83450 267.72342)))
("SF_PLANTING" 0 ((12469.83450 252.63857) (12484.91663 238.76143) (12511.31222 233.79299) (12564.10215 242.53122)
(12579.18552 256.41120)))
("SF_SOLAR" 0 ((12473.60441 8118.40113) (12473.60441 8110.85973)))
("SF_SOLAR" 0 ((12473.60441 8024.13281) (12473.60441 8031.67421)))
("SF_PLANTING" 0 ((12564.10215 7121.04072) (12541.47771 7114.32862) (12485.06572 7062.59400) (12474.66075 7043.74084)
(12473.60441 7021.11640)))
("SF_PLANTING" 0 ((12526.39559 7021.11640) (12515.08337 7024.73201) (12473.60441 7021.11640)))
("SF_PLANTING" 0 ((12473.60441 6779.78857) (12481.14672 6772.24762)))
("SF_PLANTING" 0 ((12500.00000 358.22115) (12482.20317 343.13145) (12473.60441 316.74208)))
("SF_PLANTING" 0 ((12473.60441 316.74208) (12499.84536 328.20271) (12507.54106 354.44853)))
("SF_PLANTING" 0 ((12484.91663 6738.31097) (12477.37557 6742.08145)))
("SF_PLANTING" 0 ((12477.37557 6742.08145) (12454.75113 6741.02545) (12444.65000 6734.39186) (12444.50215 6726.99842)
(12451.12907 6715.69310) (12466.06335 6705.43032) (12484.91663 6708.14480)))
("SF_PLANTING" 0 ((12477.37557 6742.08145) (12481.14672 6772.24762)))
("SF_ARCHITECTURE" 0 ((12477.37557 5701.35747) (12511.31222 5701.35747)))
("SF_ARCHITECTURE" 0 ((12477.37557 5701.35747) (12477.53020 5659.87941) (12492.45894 5641.02557)))
("SF_SOLAR" 0 ((12481.14672 8129.71335) (12488.68778 8125.94276) (12488.68778 8122.17195)))
("SF_SOLAR" 0 ((12481.14672 7982.65452) (12481.14672 7990.19615)))
("SF_PLANTING" 0 ((12609.35102 6851.43314) (12594.26889 6837.55396) (12564.10215 6832.72749) (12511.31222 6845.08258)
(12485.07127 6862.88631) (12481.14672 6870.28631)))
("SF_PLANTING" 0 ((12549.02002 6889.14027) (12537.70781 6885.52421) (12503.77115 6891.70645) (12481.14672 6870.28631)))
("SF_PLANTING" 0 ((12518.85328 6783.55984) (12481.14672 6772.24762)))
("SF_MASONRY_AND_ARCH" 0 ((12571.64446 1817.49717) (12537.70781 1813.72455) (12481.14672 1817.49717)))
("SF_PLANTING" 0 ((12590.49774 441.17647) (12545.10113 505.27998) (12481.14672 580.69287)))
("SF_PLANTING" 0 ((12500.00000 358.22115) (12481.14672 384.61538)))
("SF_PLANTING" 0 ((12484.91663 399.69740) (12481.14672 384.61538)))
("SF_PLANTING" 0 ((12484.91663 6738.31097) (12484.91663 6708.14480)))
("SF_PLANTING" 0 ((12484.91663 6738.31097) (12537.70781 6749.46833) (12579.18552 6749.62319)))
("SF_PLANTING" 0 ((12484.91663 6708.14480) (12498.94367 6685.52036) (12500.00000 6655.35419)))
("SF_MASONRY_AND_ARCH" 0 ((12484.91663 1693.06278) (12482.34400 1677.97794) (12500.00000 1644.04129)))
("SF_PLANTING" 0 ((12507.54106 429.86425) (12488.68778 437.10283) (12473.76595 426.09446) (12471.04559 418.55204)
(12484.91663 399.69740)))
("SF_PLANTING" 0 ((12507.54106 429.86425) (12499.84536 411.01719) (12484.91663 399.69740)))
("SF_MASONRY_AND_ARCH" 0 ((12488.68778 1745.85124) (12503.77115 1753.39367)))
("SF_PLANTING" 0 ((12549.02002 708.89989) (12515.08337 705.28258) (12488.68778 708.89989)))
("SF_ARCHITECTURE" 0 ((12492.45894 3895.17387) (12492.45894 5641.02557)))
("SF_ARCHITECTURE" 0 ((12492.45894 5641.02557) (12511.31222 5659.87941) (12511.31222 5701.35747)))
("SF_SOLAR" 0 ((12496.22885 8197.58665) (12496.22885 8205.12828)))
("SF_SOLAR" 0 ((12503.77115 8144.79638) (12496.22885 8152.33778)))
("SF_PLANTING" 0 ((12496.22885 6930.61867) (12545.24887 6938.15962)))
("SF_SOLAR" 0 ((12669.68326 8107.08891) (12650.82998 8099.69559) (12601.80995 8099.39955) (12586.72658 8095.78326)
(12552.78993 8095.92477) (12530.16550 8103.17025) (12500.00000 8103.31833)))
("SF_PLANTING" 0 ((12500.00000 6655.35419) (12510.11505 6647.80633) (12514.03394 6636.50102) (12515.08337 6598.79310)))
("SF_PLANTING" 0 ((12500.00000 358.22115) (12507.54106 354.44853)))
("SF_SOLAR" 0 ((12511.31222 8080.69389) (12503.77115 8069.38167)))
("SF_SOLAR" 0 ((12503.77115 8024.13281) (12503.77115 8031.67421)))
("SF_SOLAR" 0 ((12503.77115 7982.65452) (12503.77115 7990.19615)))
("SF_SOLAR" 0 ((12507.54106 7926.09355) (12503.77115 7918.55204)))
("SF_PLANTING" 0 ((12503.77115 6538.46154) (12501.19717 6557.31550) (12512.50396 6587.32647) (12518.85328 6591.25215)))
("SF_MASONRY_AND_ARCH" 0 ((12503.77115 1760.93609) (12503.77115 1753.39367)))
("SF_MASONRY_AND_ARCH" 0 ((12503.77115 1753.39367) (12530.16550 1749.62387)))
("SF_SOLAR" 0 ((12515.08337 8212.66968) (12507.54106 8216.44050)))
("SF_PLANTING" 0 ((12518.85328 6783.55984) (12507.54106 6809.95475)))
("SF_MASONRY_AND_ARCH" 0 ((12518.85328 2858.22048) (12508.59740 2846.90826) (12507.54106 2824.28382)))
("SF_MASONRY_AND_ARCH" 0 ((12507.54106 2824.28382) (12533.92975 2824.43156) (12541.47771 2828.05430)))
("SF_PLANTING" 0 ((12507.54106 429.86425) (12537.70781 441.17647)))
("SF_PLANTING" 0 ((12515.08337 354.44853) (12507.54106 354.44853)))
("SF_SOLAR" 0 ((12530.16550 8163.65000) (12522.61753 8169.99389) (12511.31222 8171.19163)))
("SF_ARCHITECTURE" 0 ((12564.10215 5693.81606) (12549.01957 5704.07229) (12533.93665 5712.51505) (12511.31222
5707.70781) (12511.31222 5701.35747)))
("SF_PLANTING" 0 ((12511.31222 279.03563) (12518.86018 275.55995) (12533.93665 280.08439) (12560.33224 301.66007)))
("SF_PLANTING" 0 ((12541.47771 324.28450) (12516.28066 301.65249) (12511.31222 279.03563)))
("SF_SOLAR" 0 ((12515.08337 8088.23529) (12526.39559 8088.23529)))
("SF_PLANTING" 0 ((12518.85328 6591.25215) (12515.08337 6598.79310)))
("SF_MASONRY_AND_ARCH" 0 ((12590.49774 1044.49378) (12515.08337 1040.72398)))
("SF_PLANTING" 0 ((12515.08337 354.44853) (12530.16550 340.42285) (12541.47771 335.59672)))
("SF_PLANTING" 0 ((12515.08337 354.44853) (12559.13371 411.00962) (12564.10215 429.86425)))
("SF_PLANTING" 0 ((12658.37104 6779.78857) (12631.97545 6783.55328) (12582.95667 6779.94344) (12571.64446 6783.41154)
(12518.85328 6783.55984)))
("SF_PLANTING" 0 ((12526.39559 6591.25215) (12518.85328 6591.25215)))
("SF_MASONRY_AND_ARCH" 0 ((12518.85328 2582.95600) (12537.70781 2582.95600)))
("SF_SOLAR" 0 ((12609.35102 7779.03473) (12609.19627 7846.90803) (12605.42647 7854.44287) (12594.26889 7861.83631)
(12537.70781 7862.13903) (12522.62443 7865.76165)))
("SF_PLANTING" 0 ((13069.38201 6478.12964) (13020.36199 6481.89389) (12522.62443 6481.90045)))
("SF_PLANTING" 0 ((12526.39559 6549.77376) (12533.63428 6530.91980) (12522.77217 6508.29570) (12522.62443 6481.90045)))
("SF_SOLAR" 0 ((12692.30769 8141.02557) (12537.70781 8141.03213) (12526.39559 8144.79638)))
("SF_PLANTING" 0 ((12526.39559 7021.11640) (12526.39559 7009.80419)))
("SF_PLANTING" 0 ((12530.16550 7032.42862) (12526.39559 7021.11640)))
("SF_PLANTING" 0 ((12567.87330 7006.03292) (12526.39559 7009.80419)))
("SF_PLANTING" 0 ((12526.39559 859.72851) (12530.16550 871.04072)))
("SF_PLANTING" 0 ((12526.39559 791.85520) (12526.39559 844.64649)))
("SF_PLANTING" 0 ((12526.39559 791.85520) (12537.70781 788.08541)))
("SF_SOLAR" 0 ((12711.16097 8163.65000) (12530.16550 8163.65000)))
("SF_MASONRY_AND_ARCH" 0 ((12530.16550 901.20758) (12541.47771 908.74717)))
("SF_MASONRY_AND_ARCH" 0 ((12537.70781 3171.19129) (12527.74751 3190.04525) (12533.93665 3220.21143)))
("SF_SOLAR" 0 ((12537.70781 8114.63054) (12631.97545 8114.63054)))
("SF_PLANTING" 0 ((12545.24887 6685.52036) (12537.70781 6696.83258)))
("SF_MASONRY_AND_ARCH" 0 ((12537.70781 3118.40147) (12537.70781 3133.48416)))
("SF_MASONRY_AND_ARCH" 0 ((12541.47771 2944.94695) (12537.70781 2993.96708)))
("SF_MASONRY_AND_ARCH" 0 ((12537.70781 2533.93665) (12537.70781 2526.39491)))
("SF_MASONRY_AND_ARCH" 0 ((12552.78993 2254.90170) (12537.70781 2254.90170)))
("SF_PLANTING" 0 ((12537.70781 441.17647) (12564.10215 429.86425)))
("SF_MASONRY_AND_ARCH" 0 ((12541.47771 3310.70916) (12541.47771 3359.72851)))
("SF_PLANTING" 0 ((12541.47771 324.28450) (12541.47771 335.59672)))
("SF_PLANTING" 0 ((12586.72658 339.36652) (12579.17862 349.47387) (12564.10215 350.52410) (12541.47771 335.59672)))
("SF_PLANTING" 0 ((12541.47771 324.28450) (12560.33224 301.66007)))
("SF_SOLAR" 0 ((12545.24887 7952.48869) (12549.02002 7960.03020)))
("SF_PLANTING" 0 ((12549.02002 6889.14027) (12552.49434 6923.07692) (12545.24887 6938.15962)))
("SF_PLANTING" 0 ((12579.18552 6972.09627) (12545.24887 6938.15962)))
("SF_SOLAR" 0 ((12549.02002 8125.94276) (12549.02002 8133.48416)))
("SF_SOLAR" 0 ((12549.02002 8069.38167) (12549.02002 8084.46448)))
("SF_SOLAR" 0 ((12549.02002 8024.13281) (12549.02002 8031.67421)))
("SF_PLANTING" 0 ((12594.26889 6881.59853) (12560.33224 6881.75339) (12549.02002 6889.14027)))
("SF_MASONRY_AND_ARCH" 0 ((12549.02002 1749.62387) (12605.58111 1753.54140) (12643.28767 1760.78767) (12726.24434
1757.17036) (12786.57658 1763.50792) (12843.13767 1762.13948) (12858.21980 1772.24830)))
("SF_MASONRY_AND_ARCH" 0 ((12549.02002 1595.02262) (12598.03880 1602.41663) (12722.46629 1602.71833) (12729.86086
1610.11222) (12730.01550 1632.72907)))
("SF_MASONRY_AND_ARCH" 0 ((12552.78993 1184.01210) (12579.17862 1184.01210) (12586.72658 1184.01210)))
("SF_SOLAR" 0 ((12613.12217 8009.04977) (12611.92500 8001.50170) (12587.78292 7971.34231) (12556.56109 7918.55204)))
("SF_MASONRY_AND_ARCH" 0 ((12564.10215 2043.74084) (12556.56109 2043.74084)))
("SF_ARCHITECTURE" 0 ((12564.10215 5693.81606) (12564.09525 3857.46606) (12560.33224 3846.15385)))
("SF_MASONRY_AND_ARCH" 0 ((12560.33224 2088.98971) (12556.85656 2077.68371) (12560.33224 2070.13575)))
("SF_MASONRY_AND_ARCH" 0 ((12730.01550 2111.61414) (12725.04717 2096.54378) (12718.69638 2091.24333) (12571.64446
2092.75396) (12560.33224 2088.98971)))
("SF_PLANTING" 0 ((12560.33224 301.66007) (12567.87330 301.66007)))
("SF_PLANTING" 0 ((12564.10215 7121.04072) (12564.24989 7073.90622) (12571.64446 7036.19910)))
("SF_ARCHITECTURE" 0 ((12567.87330 7582.95622) (12564.10905 7567.87330) (12564.10215 7121.04072)))
("SF_PLANTING" 0 ((12564.10215 7121.04072) (12590.49774 7122.77805) (12605.58111 7119.15509)))
("SF_ARCHITECTURE" 0 ((12564.10215 5693.81606) (12582.95622 5707.69468) (12601.80995 5710.57036) (12616.89333
5707.69468) (12631.97545 5693.81606)))
("SF_PLANTING" 0 ((12564.10215 527.90441) (12579.18552 527.90441)))
("SF_PLANTING" 0 ((12590.49774 441.17647) (12579.18552 431.06912) (12564.10215 429.86425)))
("SF_SOLAR" 0 ((12571.64446 7997.73756) (12567.87330 7986.42534)))
("SF_ARCHITECTURE" 0 ((12567.87330 7775.26391) (12567.87330 7635.74661)))
("SF_ARCHITECTURE" 0 ((12609.35102 7779.03473) (12601.80305 7775.41199) (12567.87330 7775.26391)))
("SF_ARCHITECTURE" 0 ((12594.26889 7635.74661) (12567.87330 7635.74661)))
("SF_ARCHITECTURE" 0 ((12567.87330 7582.95622) (12582.80758 7587.78326) (12593.07036 7601.80995) (12594.26889
7635.74661)))
("SF_PLANTING" 0 ((12579.18552 6972.09627) (12567.87330 7006.03292)))
("SF_PLANTING" 0 ((12567.87330 7006.03292) (12571.64446 7036.19910)))
("SF_MASONRY_AND_ARCH" 0 ((12567.87330 2383.10735) (12730.01550 2383.10735)))
("SF_PLANTING" 0 ((12579.18552 256.41120) (12567.87330 301.66007)))
("SF_PLANTING" 0 ((12586.72658 339.36652) (12567.87330 301.66007)))
("SF_SOLAR" 0 ((12571.64446 8069.38167) (12571.64446 8084.46448)))
("SF_SOLAR" 0 ((12571.64446 8024.13281) (12571.64446 8039.21561)))
("SF_SOLAR" 0 ((12586.72658 8046.75724) (12571.64446 8039.21561)))
("SF_PLANTING" 0 ((12605.58111 7028.65735) (12571.64446 7036.19910)))
("SF_PLANTING" 0 ((12579.18552 6972.09627) (12601.80995 6972.09627)))
("SF_MASONRY_AND_ARCH" 0 ((12579.18552 1436.65158) (12579.18552 1447.96380)))
("SF_MASONRY_AND_ARCH" 0 ((12971.34197 1436.65158) (12914.78088 1433.03507) (12892.15090 1454.30136) (12828.05430
1459.27602) (12805.42986 1455.51109) (12654.59989 1455.35781) (12635.74661 1450.53643) (12605.58111 1433.93744)
(12579.18552 1436.65158)))
("SF_PLANTING" 0 ((12601.80995 441.17647) (12609.19627 456.25848) (12604.52477 493.96776) (12596.98235 509.04977)
(12579.18552 527.90441)))
("SF_PLANTING" 0 ((12579.18552 527.90441) (12582.95667 550.52885)))
("SF_PLANTING" 0 ((12579.18552 256.41120) (12628.20554 238.60600) (12654.59989 237.56346) (12665.91210 241.48167)
(12684.76663 260.18100)))
("SF_MASONRY_AND_ARCH" 0 ((12582.95667 1134.99152) (12643.28767 1135.13993) (12662.14219 1138.76414) (12786.57658
1138.75724) (12820.51324 1134.99152)))
("SF_PLANTING" 0 ((12582.95667 550.52885) (12598.03880 550.38043) (12635.74661 539.21663)))
("SF_SOLAR" 0 ((12786.57658 7941.17647) (12748.86878 7937.40600) (12722.47319 7941.17647) (12639.51776 7941.02839)
(12628.20554 7937.56041) (12609.35102 7941.02183) (12594.27579 7937.56041) (12586.72658 7941.17647)))
("SF_MASONRY_AND_ARCH" 0 ((12586.72658 1523.37952) (12590.49774 1534.69174)))
("SF_PLANTING" 0 ((12613.12217 335.59672) (12586.72658 339.36652)))
("SF_MASONRY_AND_ARCH" 0 ((12590.49774 2039.96957) (12601.80995 2043.73394) (12624.43439 2039.96957)))
("SF_PLANTING" 0 ((12590.49774 863.49830) (12601.80995 862.44265) (12612.97443 855.81029) (12647.95362 806.93722)
(12683.71029 723.98190) (12714.78439 607.08993) (12722.17760 565.61086) (12717.51165 550.52885) (12692.15995 497.88597)
(12665.91210 486.42534)))
("SF_PLANTING" 0 ((12635.74661 584.46550) (12624.58903 595.77771) (12624.28665 652.33880) (12615.83699 690.04525)
(12605.72896 712.66968) (12605.43337 754.14876) (12594.42364 784.31278) (12586.87432 852.18609) (12590.49774
863.49830)))
("SF_PLANTING" 0 ((12594.26889 871.04072) (12590.49774 863.49830)))
("SF_PLANTING" 0 ((12601.80995 441.17647) (12590.49774 441.17647)))
("SF_SOLAR" 0 ((12594.26889 8076.92308) (12594.26889 8069.38167)))
("SF_SOLAR" 0 ((12594.26889 7914.78133) (12601.80995 7929.86425)))
("SF_ARCHITECTURE" 0 ((16304.67760 7635.74661) (15637.25679 7635.74661) (15614.63235 7635.74661) (15554.29864
7635.74661) (15282.80543 7635.74661) (15260.18100 7635.74661) (14679.48676 7635.74661) (14656.86233 7635.74661)
(14600.30124 7635.74661) (14581.44796 7635.74661) (14076.16934 7635.74661) (14057.31482 7635.74661) (12594.26889
7635.74661)))
("SF_PLANTING" 0 ((12594.26889 6881.59853) (12609.35102 6851.43314)))
("SF_PLANTING" 0 ((12594.26889 6881.59853) (12597.14389 6900.44593) (12609.35102 6911.76471)))
("SF_PLANTING" 0 ((12609.35102 6957.01357) (12601.80995 6972.09627)))
("SF_PLANTING" 0 ((12601.80995 6972.09627) (12613.12217 6994.72070)))
("SF_PLANTING" 0 ((12620.66324 411.00962) (12601.80995 441.17647)))
("SF_PLANTING" 0 ((12605.58111 7028.65735) (12613.12217 6994.72070)))
("SF_PLANTING" 0 ((12605.58111 7028.65735) (12620.66324 7036.19910)))
("SF_SOLAR" 0 ((12609.35102 7978.88394) (12616.89333 7975.11312)))
("SF_SOLAR" 0 ((12639.51776 7869.53247) (12631.96855 7872.93462) (12609.35102 7865.76165)))
("SF_ARCHITECTURE" 0 ((16315.98982 7775.26391) (16270.74095 7771.64785) (16248.11652 7775.26391) (12624.43439
7775.26391) (12609.35102 7779.03473)))
("SF_ARCHITECTURE" 0 ((12624.43439 7571.64400) (12620.66324 7571.64400) (12609.35102 7571.64400)))
("SF_PLANTING" 0 ((12609.35102 6957.01357) (12605.58801 6934.38914) (12609.35102 6911.76471)))
("SF_PLANTING" 0 ((12609.35102 6957.01357) (12635.59197 6961.98835) (12643.28767 6983.40848)))
("SF_PLANTING" 0 ((12647.05882 6907.99423) (12609.35102 6911.76471)))
("SF_PLANTING" 0 ((12647.05882 6851.43314) (12609.35102 6851.43314)))
("SF_SOLAR" 0 ((12658.37104 8065.61086) (12650.97093 8061.68541) (12613.12217 8009.04977)))
("SF_SOLAR" 0 ((12658.37104 8012.82059) (12651.87262 8008.89514) (12634.69027 7978.88394) (12613.12217 7952.48869)))
("SF_PLANTING" 0 ((12643.28767 6983.40848) (12639.36312 6989.75249) (12613.12217 6994.72070)))
("SF_PLANTING" 0 ((12613.12217 335.59672) (12614.32636 324.28450) (12643.43676 286.57523) (12654.59989 276.46165)
(12677.22432 267.72342)))
("SF_PLANTING" 0 ((12613.12217 335.59672) (12631.97545 354.44853)))
("SF_SOLAR" 0 ((12616.89333 8133.48416) (12616.89333 8122.17195)))
("SF_MASONRY_AND_ARCH" 0 ((12624.43439 1862.74536) (12616.89333 1862.74536)))
("SF_MASONRY_AND_ARCH" 0 ((13024.13314 1809.95475) (13005.27862 1810.10249) (12978.88428 1817.49627) (12631.97545
1817.49627) (12620.81787 1813.57127) (12616.89333 1798.64253)))
("SF_SOLAR" 0 ((12620.66324 8069.38167) (12620.66324 8084.46448)))
("SF_PLANTING" 0 ((12654.59989 7032.42862) (12620.66324 7036.19910)))
("SF_PLANTING" 0 ((12654.59989 7138.00905) (12621.71957 7077.67749) (12620.66324 7036.19910)))
("SF_PLANTING" 0 ((12620.66324 411.00962) (12665.91210 396.97704) (12680.99548 395.92760)))
("SF_PLANTING" 0 ((12620.66324 411.00962) (12620.81097 395.92760) (12631.97545 354.44853)))
("SF_ARCHITECTURE" 0 ((15546.75713 7567.87330) (15535.44683 7571.49593) (15509.04977 7567.88643) (15486.42534
7571.64400) (12639.51776 7571.64400) (12624.43439 7571.64400)))
("SF_ARCHITECTURE" 0 ((12624.43439 7175.71618) (12624.43439 7571.64400)))
("SF_MASONRY_AND_ARCH" 0 ((12673.45441 2217.19457) (12647.05882 2213.57183) (12624.43439 2220.96505)))
("SF_MASONRY_AND_ARCH" 0 ((12624.43439 2220.96505) (12631.97545 2243.58948)))
("SF_MASONRY_AND_ARCH" 0 ((12624.43439 2039.96957) (12628.05781 2024.88688) (12624.44683 1998.49197) (12628.20554
1975.86753)))
("SF_MASONRY_AND_ARCH" 0 ((12809.20102 2043.74084) (12790.34649 2039.97647) (12767.72206 2043.73462) (12639.51776
2043.73462) (12624.43439 2039.96957)))
("SF_MASONRY_AND_ARCH" 0 ((12677.22432 1184.01210) (12624.43439 1184.01210)))
("SF_MASONRY_AND_ARCH" 0 ((12628.20509 2575.41505) (12628.20509 2545.40181)))
("SF_MASONRY_AND_ARCH" 1 ((12628.20509 2545.40181) (12605.58111 2545.40351) (12594.26844 2556.56109) (12594.26844
2605.58043) (12594.26844 2620.66391) (12594.26844 2684.76595) (12594.26844 2699.84943) (12594.26844 2779.03495)
(12594.26844 2801.65939) (12594.26844 2831.82477) (12594.26844 3159.87907) (12594.26844 3197.58699) (12594.26844
3220.21143) (12594.26844 3374.81120) (12605.58111 3385.96878) (12714.93213 3385.96878) (12722.31844 3382.19830)
(12726.23744 3371.04072) (12726.08971 2556.56799) (12722.31844 2550.22353) (12696.07885 2545.39661)))
("SF_MASONRY_AND_ARCH" 0 ((12628.20509 2545.40181) (12628.20509 2545.24887)))
("SF_SOLAR" 0 ((12635.74661 8005.27896) (12628.20554 8009.04977)))
("SF_SOLAR" 0 ((12730.01550 7839.36652) (12628.20554 7839.36652)))
("SF_ARCHITECTURE" 0 ((12628.20554 3846.15385) (12631.96855 3857.46606) (12631.97545 5693.81606)))
("SF_MASONRY_AND_ARCH" 0 ((12628.20554 1941.93088) (12628.20554 1926.84740)))
("SF_MASONRY_AND_ARCH" 0 ((12839.36652 1926.84740) (12741.32771 1926.84118) (12722.47319 1923.09005) (12707.39106
1926.69966) (12628.20554 1926.84740)))
("SF_SOLAR" 0 ((12631.97545 7926.09355) (12631.97545 7918.55204)))
("SF_ARCHITECTURE" 0 ((12707.39106 5697.58665) (12677.22432 5712.37353) (12650.82952 5707.84242) (12631.97545
5693.81606)))
("SF_MASONRY_AND_ARCH" 0 ((12631.97545 1263.19853) (12662.14219 1263.19853)))
("SF_PLANTING" 0 ((12650.82998 354.44853) (12631.97545 354.44853)))
("SF_PLANTING" 0 ((12635.74661 584.46550) (12650.82998 584.46550)))
("SF_PLANTING" 0 ((12635.74661 584.46550) (12635.74661 539.21663)))
("SF_PLANTING" 0 ((12654.59989 531.67421) (12635.74661 539.21663)))
("SF_MASONRY_AND_ARCH" 0 ((12639.51776 1052.03620) (12639.51776 1059.57862)))
("SF_MASONRY_AND_ARCH" 0 ((12639.51776 1052.03620) (12673.45441 1048.26640) (12779.03428 1055.65271) (12809.20102
1052.03620)))
("SF_PLANTING" 0 ((12639.51776 705.12726) (12639.51776 712.66968)))
("SF_PLANTING" 0 ((12650.82998 6987.17975) (12643.28767 6983.40848)))
("SF_MASONRY_AND_ARCH" 0 ((12748.86878 908.74717) (12673.45441 904.98360) (12643.28767 912.51980)))
("SF_SOLAR" 0 ((12647.05882 7978.88394) (12760.18100 7982.50656) (12786.57658 7975.40928) (12805.42296 7981.45679)
(12812.97093 7978.88394)))
("SF_PLANTING" 0 ((12647.05882 6907.99423) (12650.82998 6896.68201)))
("SF_PLANTING" 0 ((12662.14219 6934.38914) (12647.05882 6907.99423)))
("SF_PLANTING" 0 ((12647.05882 6851.43314) (12658.37104 6844.04627) (12703.61991 6844.03971) (12714.93213 6847.66188)))
("SF_PLANTING" 0 ((12647.05882 6851.43314) (12650.82998 6896.68201)))
("SF_PLANTING" 0 ((12684.76663 6896.68201) (12650.82998 6896.68201)))
("SF_PLANTING" 0 ((12650.82998 584.46550) (12661.98756 569.37579) (12661.98756 546.75622) (12654.59989 531.67421)))
("SF_PLANTING" 0 ((12673.45441 629.71437) (12655.80396 618.25373) (12650.82998 584.46550)))
("SF_PLANTING" 0 ((12650.82998 354.44853) (12659.56821 320.51188) (12672.39808 294.11765) (12677.22432 267.72342)))
("SF_PLANTING" 0 ((12684.76663 373.30317) (12650.82998 354.44853)))
("SF_PLANTING" 0 ((12665.91210 7021.11640) (12654.59989 7032.42862)))
("SF_PLANTING" 0 ((12654.59989 7032.42862) (12658.37104 7055.05305)))
("SF_PLANTING" 0 ((12654.59989 531.67421) (12658.52568 497.73756) (12665.91210 486.42534)))
("SF_SOLAR" 0 ((12662.14219 8133.48416) (12658.37104 8118.40113)))
("SF_SOLAR" 0 ((12658.37104 8065.61086) (12665.91210 8058.06946)))
("SF_SOLAR" 0 ((12711.16097 8163.65000) (12709.95679 8152.33778) (12663.19864 8080.69389) (12658.37104 8065.61086)))
("SF_SOLAR" 0 ((12839.36652 8012.82059) (12692.30769 8012.81403) (12673.45441 8009.05645) (12658.37104 8012.82059)))
("SF_SOLAR" 0 ((12724.35939 8118.40113) (12659.56821 8020.36867) (12658.37104 8012.82059)))
("SF_PLANTING" 0 ((12658.37104 6779.78857) (12662.14219 6753.39367)))
("SF_PLANTING" 0 ((12658.37104 6779.78857) (12680.99548 6783.55984) (12816.74208 6783.55328) (12839.36652 6779.78891)
(12880.84423 6783.55328) (12895.92760 6779.93688) (12937.40532 6779.78857)))
("SF_SOLAR" 0 ((12662.14219 7956.25939) (12662.14219 7967.57172)))
("SF_PLANTING" 0 ((12662.14219 6934.38914) (12684.76663 6930.61867)))
("SF_PLANTING" 0 ((12662.14219 6934.38914) (12665.91210 6941.93088)))
("SF_MASONRY_AND_ARCH" 0 ((12673.45441 3438.91403) (12665.91210 3438.91403)))
("SF_PLANTING" 0 ((12680.99548 395.92760) (12669.83100 441.17647) (12665.91210 486.42534)))
("SF_SOLAR" 0 ((12673.45441 7869.53247) (12703.61991 7869.53247)))
("SF_MASONRY_AND_ARCH" 0 ((12673.45441 2217.19457) (12699.84876 2212.36765) (12737.55656 2198.48914) (12760.18100
2202.10566) (12895.92760 2202.11188)))
("SF_MASONRY_AND_ARCH" 0 ((12673.45441 2217.19457) (12674.65860 2243.58326) (12684.76663 2250.97658) (12711.16097
2247.65690) (12748.86878 2251.27964) (12771.49321 2258.51833) (12846.90758 2252.32919) (12861.99095 2254.74706)
(12903.46867 2247.36075)))
("SF_MASONRY_AND_ARCH" 0 ((12692.30769 1421.56957) (12673.45441 1425.33937)))
("SF_PLANTING" 0 ((12673.45441 878.58314) (12707.39106 882.35294)))
("SF_SOLAR" 0 ((12677.22432 8080.69389) (12684.76663 8073.15226)))
("SF_PLANTING" 0 ((12677.22432 267.72342) (12684.76663 260.18100)))
("SF_PLANTING" 0 ((12684.76663 373.30317) (12680.99548 395.92760)))
("SF_MASONRY_AND_ARCH" 0 ((12682.88088 1184.01210) (12684.76618 1184.01210) (12686.65158 1184.01210)))
("SF_SOLAR" 0 ((12684.76663 7997.73756) (12684.76663 7990.19615)))
("SF_SOLAR" 0 ((12684.76663 7956.25939) (12684.76663 7963.80090)))
("SF_PLANTING" 0 ((12684.76663 6896.68201) (12684.76663 6930.61867)))
("SF_PLANTING" 0 ((12684.76663 6930.61867) (12693.51188 6957.01357) (12707.39106 6968.32579)))
("SF_PLANTING" 0 ((12684.76663 6896.68201) (12707.39106 6896.68201)))
("SF_PLANTING" 0 ((12684.76663 373.30317) (12697.27613 328.06052) (12722.47319 309.19966)))
("SF_PLANTING" 0 ((12696.07885 260.18100) (12684.76663 260.18100)))
("SF_PLANTING" 0 ((12688.53654 7032.42862) (12703.76765 7062.44615) (12718.70328 7069.98088) (12728.81143 7066.21041)
(12730.01550 7039.96957)))
("SF_MASONRY_AND_ARCH" 0 ((12726.24434 995.47511) (12699.84876 999.09163) (12688.53654 995.47511)))
("SF_SOLAR" 0 ((12692.30769 8182.50385) (12692.30769 8174.96222)))
("SF_SOLAR" 0 ((12703.61991 8103.31833) (12692.30769 8107.08891)))
("SF_SOLAR" 0 ((12692.30769 8042.98643) (12752.63993 8039.21561)))
("SF_PLANTING" 0 ((12692.30769 6987.17975) (12703.46527 6979.63145) (12707.39106 6968.32579)))
("SF_PLANTING" 0 ((12763.95215 252.63857) (12748.86878 241.48167) (12714.93213 241.48167) (12703.62681 248.87500)
(12696.07885 260.18100)))
("SF_PLANTING" 0 ((12696.07885 260.18100) (12715.98156 290.19253) (12722.47319 294.11765)))
("SF_SOLAR" 0 ((12699.84876 8061.84005) (12869.53201 8061.84005)))
("SF_SOLAR" 0 ((12699.84876 8024.13281) (12707.39106 8035.44502)))
("SF_PLANTING" 0 ((12699.84876 6738.31097) (12895.92760 6738.31097)))
("SF_SOLAR" 0 ((12707.39106 8133.48416) (12724.35939 8118.40113)))
("SF_SOLAR" 0 ((12707.39106 7952.48869) (12707.39106 7971.34231)))
("SF_SOLAR" 0 ((12707.39106 7929.86425) (12707.39106 7918.55204)))
("SF_PLANTING" 0 ((12733.78541 6915.53518) (12725.33575 6953.24310) (12718.55419 6964.40045) (12707.39106 6968.32579)))
("SF_PLANTING" 0 ((12707.39106 6896.68201) (12707.54581 6866.51584) (12714.93213 6847.66188)))
("SF_PLANTING" 0 ((12733.78541 6907.99423) (12714.93903 6903.02557) (12707.39106 6896.68201)))
("SF_ARCHITECTURE" 0 ((12707.39106 5697.58665) (12703.61991 5641.02557) (12703.62681 5282.80543) (12707.39106
5260.18100) (12707.38416 4468.32579) (12703.61991 4445.70136) (12707.38416 4132.73043) (12703.62681 4113.87590)
(12703.62681 3981.90045) (12707.24333 3966.81708) (12707.38416 3906.48609) (12703.62681 3861.23722) (12708.44751
3846.16007) (12718.70328 3838.61278)))
("SF_ARCHITECTURE" 0 ((12760.18100 5705.12828) (12752.63303 5708.75068) (12730.01550 5708.75068) (12707.39106
5697.58665)))
("SF_MASONRY_AND_ARCH" 0 ((12707.39106 1421.56957) (12718.70328 1420.36471) (12730.01550 1410.25735)))
("SF_MASONRY_AND_ARCH" 0 ((12714.93213 1233.03167) (12707.39106 1236.80147)))
("SF_MASONRY_AND_ARCH" 0 ((12707.39106 1236.80147) (12707.54581 1251.88631) (12717.49921 1266.96833) (12722.47319
1300.90498)))
("SF_PLANTING" 0 ((12707.39106 825.79186) (12722.47319 822.02206) (12805.42986 822.02692) (12824.28314 825.79186)))
("SF_SOLAR" 0 ((12730.01550 8174.96222) (12711.16097 8163.65000)))
("SF_MASONRY_AND_ARCH" 0 ((13114.63088 1104.82658) (13054.29864 1104.82658) (12944.94762 1104.82658) (12922.32319
1104.82658) (12888.38654 1108.75192) (12878.27851 1116.14457) (12874.50034 1131.22172) (12880.54864 1168.92817)
(12873.14853 1186.57794) (12711.16097 1187.78281)))
("SF_PLANTING" 0 ((12714.93213 6847.66188) (12733.78541 6836.49796) (12771.49321 6836.49796) (12801.65181 6845.08258)
(12809.20102 6851.43314)))
("SF_MASONRY_AND_ARCH" 0 ((12718.70328 1387.63292) (12730.01550 1410.25735)))
("SF_MASONRY_AND_ARCH" 0 ((13088.23529 1338.61143) (13076.92308 1342.23563) (13042.98643 1342.38405) (13035.44536
1342.38405) (12918.55204 1342.37715) (12884.61538 1338.61833) (12850.67873 1346.00611) (12718.70328 1346.15385)))
("SF_MASONRY_AND_ARCH" 0 ((12718.70328 1346.15385) (12718.70328 1331.07183)))
("SF_PLANTING" 0 ((12722.47319 7039.96957) (12730.01550 7039.96957)))
("SF_PLANTING" 0 ((12722.47319 309.19966) (12722.47319 294.11765)))
("SF_PLANTING" 0 ((12722.47319 309.19966) (12728.82387 313.12557) (12740.27828 343.13631) (12741.47557 392.15781)
(12756.40984 437.40667)))
("SF_PLANTING" 0 ((12763.95215 252.63857) (12737.55656 282.80543) (12722.47319 294.11765)))
("SF_SOLAR" 0 ((12724.35939 8118.40113) (12733.78541 8110.85973)))
("SF_SOLAR" 0 ((12724.35939 8118.40113) (12756.40984 8169.30611)))
("SF_SOLAR" 0 ((12726.24434 8099.54751) (12752.63993 8106.94084) (12782.79853 8103.47296) (12797.89434 8114.47579)
(12880.84423 8114.63054)))
("SF_MASONRY_AND_ARCH" 0 ((12730.01550 2111.61414) (12726.24434 2130.46731)))
("SF_SOLAR" 0 ((12730.01550 8174.96222) (12741.32771 8174.96222)))
("SF_SOLAR" 0 ((12730.01550 8174.96222) (12741.32771 8197.58665)))
("SF_SOLAR" 0 ((12730.01550 8069.38167) (12730.01550 8076.92308)))
("SF_SOLAR" 0 ((12730.01550 8001.50837) (12730.01550 7990.19615)))
("SF_PLANTING" 0 ((12752.63993 7013.57466) (12733.94005 7024.89344) (12730.01550 7039.96957)))
("SF_MASONRY_AND_ARCH" 0 ((13012.82093 2111.61414) (12824.28314 2111.60792) (12801.65871 2107.84287) (12730.01550
2111.61414)))
("SF_MASONRY_AND_ARCH" 0 ((12730.01550 1410.25735) (12775.26437 1410.40441) (12786.57658 1413.87251) (12839.36652
1410.40509) (12858.21980 1421.56957)))
("SF_PLANTING" 0 ((12733.78541 6907.99423) (12733.78541 6915.53518)))
("SF_PLANTING" 0 ((12733.78541 6915.53518) (12760.18100 6920.36244) (12771.33857 6926.98914) (12775.26437 6934.38914)))
("SF_PLANTING" 0 ((12733.78541 6907.99423) (12741.32771 6900.45249)))
("SF_MASONRY_AND_ARCH" 0 ((12733.78541 1711.91459) (12731.07195 1693.06278) (12741.33326 1681.90385) (12828.05430
1681.75543) (12846.90758 1685.52036)))
("SF_SOLAR" 0 ((12737.55656 7884.61538) (12737.55656 7892.15690)))
("SF_MASONRY_AND_ARCH" 0 ((12756.40984 2496.22952) (12745.09762 2496.22952)))
("SF_SOLAR" 0 ((12748.86878 7963.80090) (12752.63993 7971.34231)))
("SF_MASONRY_AND_ARCH" 0 ((12786.57658 882.35294) (12752.79468 894.86312) (12748.86878 908.74717)))
("SF_MASONRY_AND_ARCH" 0 ((12775.26437 969.08088) (12771.78869 938.91403) (12774.06029 916.44423) (12748.86878
908.74717)))
("SF_SOLAR" 0 ((12752.63993 8178.73303) (12756.40984 8169.30611)))
("SF_SOLAR" 0 ((12752.63993 8144.79638) (12767.72206 8141.18020) (12888.38654 8141.03213) (12907.23982 8144.64186)
(12922.32319 8141.02557)))
("SF_SOLAR" 0 ((12752.63993 8084.46448) (12752.63993 8073.15226)))
("SF_SOLAR" 0 ((12752.63993 8024.13281) (12752.63993 8039.21561)))
("SF_SOLAR" 0 ((12752.63993 8039.21561) (12820.51324 8039.36369) (12839.36652 8046.75724)))
("SF_SOLAR" 0 ((12752.63993 7993.96674) (12752.63993 8001.50837)))
("SF_SOLAR" 0 ((12752.63993 7926.09355) (12752.63993 7914.78133)))
("SF_PLANTING" 0 ((12760.18100 6998.49197) (12753.83722 7002.41731) (12752.63993 7013.57466)))
("SF_PLANTING" 0 ((12763.95215 7032.42862) (12752.63993 7013.57466)))
("SF_MASONRY_AND_ARCH" 0 ((12752.63993 1263.19853) (12854.44989 1263.19853)))
("SF_SOLAR" 0 ((12756.40984 8169.30611) (12779.03428 8163.65656) (12933.63541 8163.65000)))
("SF_SOLAR" 0 ((12763.95215 8190.04525) (12756.40984 8169.30611)))
("SF_SOLAR" 0 ((12779.03428 7892.15690) (12756.40984 7850.67873)))
("SF_MASONRY_AND_ARCH" 0 ((12756.40984 2383.10735) (12779.03428 2375.56561)))
("SF_MASONRY_AND_ARCH" 0 ((12756.40984 991.70532) (12798.72432 997.98213) (12963.80090 992.90249) (12997.73756
995.46889) (13012.82093 992.00079) (13031.67421 999.24491)))
("SF_PLANTING" 0 ((12816.74208 501.50735) (12825.33258 531.67421) (12876.02489 652.33880) (12921.11912 814.47274)
(12918.39050 820.81652) (12899.69876 817.19378) (12854.59774 773.00057) (12821.71052 727.75170) (12795.16708 674.96324)
(12765.00860 599.54751) (12758.98382 569.38066) (12746.15396 542.98643) (12741.47557 520.36199) (12749.02342 448.71889)
(12756.40984 437.40667)))
("SF_PLANTING" 0 ((12816.74208 501.50735) (12802.85588 486.42534) (12798.78371 471.34333) (12786.42749 452.63710)
(12756.40984 437.40667)))
("SF_ARCHITECTURE" 0 ((12760.18100 5705.12828) (12790.34649 5705.12828)))
("SF_ARCHITECTURE" 0 ((12763.95170 5482.65419) (12763.95170 5493.96708) (12763.94525 5588.23529) (12760.18790
5607.08857) (12760.18100 5705.12828)))
("SF_ARCHITECTURE" 0 ((12763.95170 5482.65419) (12782.80543 5482.65419)))
("SF_ARCHITECTURE" 0 ((12763.95170 5482.65419) (12763.95170 5475.10690) (12763.95170 5433.64163) (12763.95170
5427.14977) (12779.03428 5422.32319)))
("SF_SOLAR" 0 ((13001.50871 7839.36652) (12763.95215 7839.36652)))
("SF_PLANTING" 0 ((12809.20102 7039.96957) (12804.37353 7051.28213) (12790.34649 7065.16097) (12775.26437 7068.93801)
(12763.95215 7066.36527)))
("SF_PLANTING" 0 ((12763.95215 7039.96957) (12763.95215 7032.42862)))
("SF_PLANTING" 0 ((12786.57658 7021.11640) (12763.95215 7032.42862)))
("SF_MASONRY_AND_ARCH" 0 ((12771.49321 2326.54627) (12763.95215 2345.39943)))
("SF_MASONRY_AND_ARCH" 0 ((12763.95215 2303.92183) (12770.29604 2311.46968) (12771.49321 2326.54627)))
("SF_PLANTING" 0 ((12763.95215 252.63857) (12790.34649 252.63857)))
("SF_MASONRY_AND_ARCH" 0 ((12771.49321 2500.00000) (12782.80543 2505.42896) (12797.88880 2500.14842) (12899.69876
2499.99378) (12914.78088 2496.22952)))
("SF_MASONRY_AND_ARCH" 0 ((12914.78088 2319.00452) (12907.23292 2325.34830) (12877.07432 2330.16833) (12854.44989
2326.55249) (12771.49321 2326.54627)))
("SF_SOLAR" 0 ((12775.26437 8125.94276) (12775.26437 8133.48416)))
("SF_SOLAR" 0 ((12775.26437 8069.38167) (12775.26437 8080.69389)))
("SF_SOLAR" 0 ((12775.26437 7993.96674) (12775.26437 8001.50837)))
("SF_SOLAR" 0 ((12775.26437 7952.48869) (12775.26437 7963.80090)))
("SF_PLANTING" 0 ((12775.26437 6968.32579) (12769.97014 6960.77749) (12775.26437 6934.38914)))
("SF_PLANTING" 0 ((12775.26437 6934.38914) (12824.28314 6949.47183)))
("SF_ARCHITECTURE" 0 ((12779.03428 4260.93473) (12779.02738 4468.32579) (12775.26437 4490.95023) (12775.27127
4607.84355) (12779.02183 4626.69683) (12775.41222 4641.78020) (12775.26437 4683.25792)))
("SF_ARCHITECTURE" 0 ((12775.26437 4683.25792) (12763.95170 4698.34129) (12763.95170 4841.62896) (12763.95170
4856.70543) (12779.03428 4864.25339)))
("SF_ARCHITECTURE" 0 ((12775.26437 4683.25792) (12797.88835 4702.11120) (12797.88835 4845.40011) (12779.03428
4864.25339)))
("SF_ARCHITECTURE" 0 ((12779.03428 4159.12477) (12775.26437 3914.02715)))
("SF_SOLAR" 0 ((12779.03428 8024.13281) (12779.03428 8031.67421)))
("SF_ARCHITECTURE" 0 ((12779.03428 5422.32319) (12779.02738 5158.37104) (12775.26437 5135.74661) (12779.03428
4864.25339)))
("SF_ARCHITECTURE" 0 ((12782.80543 5482.65419) (12790.19174 5471.34197) (12790.19174 5437.40532) (12779.03428
5422.32319)))
("SF_ARCHITECTURE" 0 ((12779.03428 4260.93473) (12794.11765 4249.62251) (12794.11765 4174.20814) (12779.03428
4159.12477)))
("SF_ARCHITECTURE" 0 ((12779.03428 4260.93473) (12763.95170 4253.38744) (12763.95170 4234.54038) (12763.95170
4174.20814) (12763.95170 4166.67330) (12779.03428 4159.12477)))
("SF_MASONRY_AND_ARCH" 0 ((12779.03428 3427.60181) (12782.96007 3422.30747) (12831.82545 3420.06007)))
("SF_MASONRY_AND_ARCH" 0 ((12779.03428 3386.12342) (12782.80543 3344.64581) (12779.03428 3306.93790)))
("SF_MASONRY_AND_ARCH" 0 ((12779.03428 3186.27477) (12789.14231 3193.96425) (12790.34649 3205.12794)))
("SF_MASONRY_AND_ARCH" 0 ((12880.84423 3118.40147) (12879.64005 3125.79468) (12873.29627 3129.55905) (12786.58348
3129.86143) (12779.03428 3133.48416)))
("SF_MASONRY_AND_ARCH" 0 ((12816.74208 3039.21595) (12816.37342 3050.15939) (12779.03428 3046.75690)))
("SF_MASONRY_AND_ARCH" 0 ((13054.29864 2733.78609) (12918.55204 2733.79231) (12895.92760 2737.55656) (12861.99095
2733.79231) (12779.03428 2733.78609)))
("SF_ARCHITECTURE" 0 ((12782.80543 5482.65419) (12790.33959 5501.50871) (12790.34649 5705.12828)))
("SF_MASONRY_AND_ARCH" 0 ((12782.80543 3269.23077) (12786.73133 3258.07319) (12794.11765 3254.30271) (12914.78088
3251.57477) (13001.50871 3257.91855)))
("SF_MASONRY_AND_ARCH" 0 ((12809.20102 2990.19581) (12782.80543 2990.19581)))
("SF_MASONRY_AND_ARCH" 0 ((12820.51324 2895.92760) (12782.80543 2888.38586)))
("SF_MASONRY_AND_ARCH" 0 ((13035.44536 2631.97613) (12933.63541 2635.74038) (12914.78088 2631.98235) (12786.73133
2630.45226) (12782.80543 2635.74661)))
("SF_PLANTING" 0 ((12782.80543 305.42986) (12797.88880 305.42986)))
("SF_PLANTING" 0 ((12790.34649 260.18100) (12779.18891 267.72828) (12775.41912 275.26301) (12776.32081 297.88258)
(12782.80543 305.42986)))
("SF_PLANTING" 0 ((12805.42986 384.61538) (12804.22568 377.06810) (12787.78077 358.22115) (12782.95317 339.36652)
(12782.80543 305.42986)))
("SF_SOLAR" 0 ((12963.80090 8197.58665) (12958.82557 8178.73303) (12942.22590 8159.87941) (12838.31018 7993.96674)
(12787.77387 7922.32285) (12786.57658 7911.01052)))
("SF_PLANTING" 0 ((12786.57658 7021.11640) (12786.72443 7002.26244) (12791.40283 6990.95679) (12824.28314 6957.01357)))
("SF_PLANTING" 0 ((12786.57658 7021.11640) (12809.20102 7039.96957)))
("SF_MASONRY_AND_ARCH" 0 ((12786.57658 2579.18552) (12801.65871 2585.52930) (12846.90758 2583.25226) (12861.99095
2586.57262) (12990.19649 2575.41505)))
("SF_PLANTING" 0 ((12786.57658 882.35294) (12783.10090 863.50588) (12786.57658 855.95871)))
("SF_MASONRY_AND_ARCH" 0 ((12786.57658 882.35294) (12794.11765 886.12274)))
("SF_ARCHITECTURE" 0 ((12790.34649 5705.12828) (12824.28314 5705.12828)))
("SF_PLANTING" 0 ((12790.34649 260.18100) (12790.34649 252.63857)))
("SF_PLANTING" 0 ((12805.42986 275.26301) (12790.34649 260.18100)))
("SF_PLANTING" 0 ((12929.86425 248.86878) (12911.01097 237.71120) (12805.42986 238.76143) (12790.34649 252.63857)))
("SF_SOLAR" 0 ((12794.11765 8092.00611) (12801.66561 8088.53801) (12816.74208 8095.62217) (12884.61538 8099.70204)
(12895.92760 8107.08891)))
("SF_PLANTING" 0 ((12805.42986 384.61538) (12794.11765 407.23982)))
("SF_SOLAR" 0 ((12797.88880 8182.50385) (12797.88880 8174.96222)))
("SF_SOLAR" 0 ((12797.88880 8122.17195) (12797.88880 8133.48416)))
("SF_SOLAR" 0 ((12797.88880 8080.69389) (12797.88880 8069.38167)))
("SF_SOLAR" 0 ((12797.88880 7986.42534) (12801.65871 7997.73756)))
("SF_PLANTING" 0 ((12805.42986 275.26301) (12798.04355 286.57523) (12797.88880 305.42986)))
("SF_PLANTING" 0 ((12843.13767 350.67873) (12828.20204 346.75362) (12797.88880 305.42986)))
("SF_MASONRY_AND_ARCH" 0 ((12805.42986 1025.64197) (12809.20102 1052.03620)))
("SF_PLANTING" 0 ((12805.42986 384.61538) (12816.58744 392.16267) (12825.33948 410.86256) (12843.13767 422.47025)
(12865.61301 444.94627) (12872.24683 456.25848) (12873.30317 471.34333)))
("SF_PLANTING" 0 ((12805.42986 275.26301) (12835.59536 286.57523)))
("SF_PLANTING" 0 ((12835.59536 7032.42862) (12809.20102 7039.96957)))
("SF_PLANTING" 0 ((12835.59536 6900.45249) (12814.16946 6881.59853) (12809.20102 6851.43314)))
("SF_PLANTING" 0 ((12809.20102 6851.43314) (12854.44989 6851.58756) (12865.76210 6858.97410)))
("SF_MASONRY_AND_ARCH" 0 ((12839.36652 2982.65486) (12820.51324 2980.09468) (12809.20102 2990.19581)))
("SF_MASONRY_AND_ARCH" 0 ((12812.97093 3001.50803) (12809.20102 2990.19581)))
("SF_MASONRY_AND_ARCH" 0 ((12809.20102 1052.03620) (12850.67873 1059.43020) (12899.69876 1059.72568) (12944.94762
1066.96493) (12963.80090 1063.35464) (13042.98643 1063.34842)))
("SF_ARCHITECTURE" 0 ((12824.28314 5705.12828) (12824.28360 3849.92500) (12824.28360 3838.76674) (12812.97093
3834.84163)))
("SF_PLANTING" 0 ((12812.97093 629.71437) (12820.51324 629.71437)))
("SF_PLANTING" 0 ((12858.21980 501.50735) (12816.74208 501.50735)))
("SF_SOLAR" 0 ((12820.51324 8069.38167) (12820.51324 8084.46448)))
("SF_SOLAR" 0 ((12820.51324 8031.67421) (12820.51324 8024.13281)))
("SF_MASONRY_AND_ARCH" 0 ((12820.51324 2895.92760) (12816.89672 2914.78156) (12820.51324 2926.09378)))
("SF_MASONRY_AND_ARCH" 0 ((13167.42081 2899.69808) (13114.63088 2892.16335) (13054.29864 2895.92760) (12892.15645
2895.92138) (12846.90758 2892.16335) (12820.51324 2895.92760)))
("SF_MASONRY_AND_ARCH" 0 ((12820.51324 2375.56561) (12854.44989 2375.56561)))
("SF_MASONRY_AND_ARCH" 0 ((12820.51324 1112.36708) (12820.51324 1097.28507)))
("SF_SOLAR" 0 ((12824.28314 7914.78133) (12922.32319 8065.61086)))
("SF_PLANTING" 0 ((12824.28314 6957.01357) (12824.28314 6949.47183)))
("SF_PLANTING" 0 ((12877.07432 6958.89921) (12824.28314 6957.01357)))
("SF_PLANTING" 0 ((12835.59536 6919.30645) (12830.62828 6945.54649) (12824.28314 6949.47183)))
("SF_ARCHITECTURE" 0 ((12824.28314 5705.12828) (12846.90758 5709.79400) (12877.07432 5693.81606)))
("SF_MASONRY_AND_ARCH" 0 ((12824.28314 2043.74084) (12861.99095 2039.96957)))
("SF_PLANTING" 0 ((12835.59536 7032.42862) (12843.14457 7017.35204) (12858.21980 7009.80419)))
("SF_PLANTING" 0 ((12835.59536 7032.42862) (12854.44989 7058.82353)))
("SF_PLANTING" 0 ((12835.59536 6900.45249) (12835.59536 6919.30645)))
("SF_PLANTING" 0 ((12869.53201 6923.07692) (12835.59536 6919.30645)))
("SF_PLANTING" 0 ((12835.59536 6900.45249) (12865.76210 6858.97410)))
("SF_PLANTING" 0 ((12892.15645 312.97229) (12861.98405 287.78009) (12843.14457 283.10158) (12835.59536 286.57523)))
("SF_PLANTING" 0 ((12858.21980 331.82410) (12840.56369 305.42986) (12835.59536 286.57523)))
("SF_MASONRY_AND_ARCH" 0 ((12839.36652 3190.04525) (12843.13767 3182.50351)))
("SF_MASONRY_AND_ARCH" 0 ((12850.67873 1240.57410) (12843.13767 1244.34389) (12839.36652 1240.57410)))
("SF_SOLAR" 0 ((12843.13767 8133.48416) (12843.13767 8122.17195)))
("SF_SOLAR" 0 ((12843.13767 8084.46448) (12846.90758 8069.38167)))
("SF_PLANTING" 0 ((12843.13767 350.67873) (12858.21980 331.82410)))
("SF_PLANTING" 0 ((12843.13767 350.67873) (12844.33495 369.53337) (12862.13869 395.92760) (12911.01097 441.02873)
(12933.63541 456.25848)))
("SF_PLANTING" 0 ((12854.44989 7058.82353) (12857.17025 7092.76018) (12835.89774 7134.23857) (12846.90758 7149.32127)))
("SF_MASONRY_AND_ARCH" 0 ((12899.69876 1681.75057) (12892.14955 1685.37262) (12846.90758 1685.52036)))
("SF_MASONRY_AND_ARCH" 0 ((12846.90758 1685.52036) (12847.05532 1711.91459) (12854.44989 1730.76923)))
("SF_SOLAR" 0 ((13024.13314 7937.40577) (12850.67873 7937.40577)))
("SF_PLANTING" 0 ((12854.44989 7058.82353) (12877.07432 7044.95170) (12888.38654 7051.28179)))
("SF_MASONRY_AND_ARCH" 0 ((12858.21980 1926.84740) (12888.38654 1934.38914)))
("SF_PLANTING" 0 ((12858.21980 501.50735) (12859.42387 486.42534) (12873.30317 471.34333)))
("SF_PLANTING" 0 ((12858.21980 501.50735) (12880.99333 535.44400) (12903.46867 557.92138) (12952.48869 590.95633)
(12982.65419 606.03281) (13035.44536 622.02421) (13069.52986 621.41867) (13068.33529 607.09197) (13061.69186 595.77771)
(12963.65317 490.34355) (12942.23281 474.96538) (12933.63541 456.25848)))
("SF_PLANTING" 0 ((12880.84423 335.59672) (12858.21980 331.82410)))
("SF_SOLAR" 0 ((12865.76210 7929.86425) (12861.99095 7918.55204)))
("SF_SOLAR" 0 ((12865.76210 8129.71335) (12865.76210 8122.17195)))
("SF_SOLAR" 0 ((12865.76210 7960.03020) (12899.69876 7963.79434) (12918.55204 7960.17828) (12971.34197 7960.17828)
(13016.59084 7963.94898) (13035.44536 7971.18767) (13046.75758 7967.57172)))
("SF_PLANTING" 0 ((12877.07432 6858.97410) (12865.76210 6858.97410)))
("SF_MASONRY_AND_ARCH" 0 ((12960.02975 3397.43563) (12948.71753 3401.05916) (12880.84423 3401.36154) (12873.45781
3405.13201) (12865.76210 3420.06007)))
("SF_MASONRY_AND_ARCH" 0 ((12865.76210 2982.65486) (12918.55204 2978.88360) (13065.61086 2978.88982) (13076.92308
2982.65486)))
("SF_PLANTING" 0 ((12869.53201 6923.07692) (12888.38654 6904.22296)))
("SF_PLANTING" 0 ((12869.53201 6923.07692) (12877.07432 6958.89921)))
("SF_PLANTING" 0 ((13005.27862 573.15328) (12941.17647 527.75600) (12888.23744 476.16946) (12873.30317 471.34333)))
("SF_PLANTING" 0 ((12877.07432 6958.89921) (12885.67172 6983.40848) (12922.32319 7021.11640)))
("SF_PLANTING" 0 ((12922.32319 6960.78405) (12877.07432 6958.89921)))
("SF_PLANTING" 0 ((12877.07432 6858.97410) (12892.15645 6847.96505) (12925.93835 6856.40136) (12941.17647 6876.77206)
(12956.25984 6881.59853)))
("SF_PLANTING" 0 ((12877.07432 6858.97410) (12887.33710 6885.36980) (12888.38654 6904.22296)))
("SF_ARCHITECTURE" 0 ((12899.69876 3831.07048) (12880.99887 3846.15385) (12877.08122 3857.46606) (12877.07432
5693.81606)))
("SF_ARCHITECTURE" 0 ((12948.71753 3797.13382) (12944.95452 3849.92500) (12944.94072 4430.61799) (12937.40577
4449.47251) (12944.94072 4498.49129) (12944.94072 5690.04525) (12941.02183 5701.35090) (12929.86425 5708.74412)
(12899.69876 5707.84242) (12877.07432 5693.81606)))
("SF_MASONRY_AND_ARCH" 0 ((12884.61538 3178.73303) (12877.07432 3182.50351)))
("SF_MASONRY_AND_ARCH" 0 ((12880.84423 2850.67873) (12877.07432 2831.82477)))
("SF_MASONRY_AND_ARCH" 0 ((12888.38654 3084.46482) (12880.84423 3080.69355)))
("SF_PLANTING" 0 ((12892.15645 312.97229) (12880.84423 335.59672)))
("SF_PLANTING" 0 ((12880.84423 335.59672) (12918.55204 368.33473) (12953.32410 373.67115) (12967.57206 387.18801)
(12982.65419 392.15781)))
("SF_PLANTING" 0 ((12920.43699 296.00396) (12895.92760 276.32014) (12880.84423 271.49321)))
("SF_SOLAR" 0 ((12884.61538 8122.17195) (12888.38654 8133.48416)))
("SF_SOLAR" 0 ((12884.61538 7944.94717) (12884.61538 7952.48869)))
("SF_MASONRY_AND_ARCH" 0 ((12884.61538 3178.73303) (12888.38654 3156.10860)))
("SF_MASONRY_AND_ARCH" 0 ((12884.61538 3178.73303) (12895.92760 3182.50351)))
("SF_MASONRY_AND_ARCH" 0 ((12903.46867 1285.82296) (12895.77296 1271.94299) (12884.61538 1270.73812)))
("SF_SOLAR" 0 ((12888.38654 7993.96674) (13001.50871 7993.97330) (13035.44536 7997.73756)))
("SF_PLANTING" 0 ((12903.46867 6904.22296) (12888.38654 6904.22296)))
("SF_MASONRY_AND_ARCH" 0 ((12888.38654 1953.24310) (12888.38654 1934.38914)))
("SF_MASONRY_AND_ARCH" 0 ((13114.63088 1926.84740) (13080.69423 1930.60554) (13061.83971 1926.85362) (12941.17647
1926.85362) (12926.09310 1930.32240) (12914.78088 1927.14367) (12888.38654 1934.38914)))
("SF_MASONRY_AND_ARCH" 0 ((12888.38654 1572.39819) (12895.77986 1557.31618) (12897.13179 1512.07217) (12907.23982
1504.67952) (12929.86425 1504.52489)))
("SF_MASONRY_AND_ARCH" 0 ((12967.57206 889.89536) (12948.71753 893.51052) (12888.38654 886.12274)))
("SF_SOLAR" 0 ((12892.15645 8061.84005) (12907.23982 8061.84005)))
("SF_MASONRY_AND_ARCH" 0 ((12892.15645 2036.19910) (12903.46867 2043.74084)))
("SF_MASONRY_AND_ARCH" 0 ((12892.15645 2002.26244) (12892.15645 1994.72070)))
("SF_PLANTING" 0 ((12920.43699 296.00396) (12903.46867 311.76674) (12892.15645 312.97229)))
("SF_MASONRY_AND_ARCH" 0 ((12895.92760 2371.79514) (12903.46867 2375.56561)))
("SF_SOLAR" 0 ((12899.69876 7975.11312) (12903.46867 7982.65452)))
("SF_MASONRY_AND_ARCH" 0 ((12899.69876 1681.75057) (13039.21527 1681.75057)))
("SF_MASONRY_AND_ARCH" 0 ((12899.69876 1681.75057) (12896.08224 1662.89593) (12899.69876 1647.81391)))
("SF_SOLAR" 0 ((13073.15192 8012.82059) (13061.83971 8009.06290) (13001.50871 8016.44321) (12903.46867 8016.59118)))
("SF_PLANTING" 0 ((12903.46867 6904.22296) (12914.78088 6900.61391) (12922.31629 6904.37783) (12933.63541 6926.84740)))
("SF_PLANTING" 0 ((12903.46867 6904.22296) (12912.20826 6923.07036) (12922.32319 6930.61867)))
("SF_MASONRY_AND_ARCH" 0 ((12907.23982 2356.71165) (12903.46867 2375.56561)))
("SF_MASONRY_AND_ARCH" 0 ((12903.46867 2375.56561) (12911.01097 2390.64830)))
("SF_MASONRY_AND_ARCH" 0 ((13133.48416 2224.73631) (12929.86425 2224.88405) (12907.39446 2229.71097) (12903.46867
2247.36075)))
("SF_MASONRY_AND_ARCH" 0 ((12911.01097 2258.67296) (12903.46867 2247.36075)))
("SF_SOLAR" 0 ((12911.01097 8084.46448) (12914.78088 8095.77670)))
("SF_MASONRY_AND_ARCH" 0 ((12911.01097 2288.83835) (12911.15882 2311.45656) (12914.78088 2319.00452)))
("SF_SOLAR" 0 ((12914.78088 8001.50837) (12914.78088 8009.04977)))
("SF_MASONRY_AND_ARCH" 0 ((12918.55204 2450.98066) (12913.11686 2466.06335) (12914.78088 2496.22952)))
("SF_MASONRY_AND_ARCH" 0 ((12914.78088 2496.22952) (12937.40532 2499.84536) (12952.48869 2496.52568) (12963.80090
2499.85226) (13024.12624 2500.15464) (13030.47704 2503.92511) (13039.21527 2526.39491)))
("SF_MASONRY_AND_ARCH" 0 ((12918.55204 2450.98066) (12911.16572 2424.58495) (12914.78088 2413.27274)))
("SF_MASONRY_AND_ARCH" 0 ((13137.25532 2319.00452) (13099.54751 2322.77500) (12929.86425 2322.76878) (12914.78088
2319.00452)))
("SF_SOLAR" 0 ((13095.77636 8046.75724) (13088.22839 8043.13439) (13031.67421 8042.83846) (13016.59084 8039.22217)
(12926.10000 8039.36369) (12918.55204 8042.98643)))
("SF_MASONRY_AND_ARCH" 0 ((13024.13314 2450.98066) (12963.80090 2454.75113) (12918.55204 2450.98066)))
("SF_PLANTING" 0 ((12920.43699 296.00396) (12925.87070 286.64355) (12929.86425 248.86878)))
("SF_PLANTING" 0 ((12920.43699 296.00396) (12926.09310 305.42986) (12929.86425 305.42986)))
("SF_SOLAR" 0 ((12922.32319 8065.61086) (12929.87115 8061.98812) (13024.13314 8061.83348) (13042.98643 8058.07602)
(13092.00645 8058.21742) (13107.08857 8061.84005)))
("SF_SOLAR" 0 ((13174.96188 8159.87941) (13163.64966 8163.64344) (12986.43224 8162.44570) (12946.00407 8107.08891)
(12922.32319 8065.61086)))
("SF_PLANTING" 0 ((12922.32319 6960.78405) (12922.32319 6930.61867)))
("SF_PLANTING" 0 ((12922.32319 6960.78405) (12930.01199 6971.94219) (12941.17647 6975.86753)))
("SF_PLANTING" 0 ((12933.63541 6926.84740) (12922.32319 6930.61867)))
("SF_SOLAR" 0 ((12929.86425 8099.54751) (12926.09310 8110.85973)))
("SF_MASONRY_AND_ARCH" 0 ((12929.86425 3186.27477) (12967.57206 3190.04525)))
("SF_MASONRY_AND_ARCH" 0 ((13118.40079 2194.57014) (13076.92308 2201.96414) (12929.86425 2202.11188)))
("SF_PLANTING" 0 ((12929.86425 305.42986) (12956.25984 305.28213) (13031.67421 282.80543)))
("SF_PLANTING" 0 ((12929.86425 305.42986) (12930.92059 316.74208) (12945.09548 342.08066) (12956.25984 346.76052)
(12997.73756 346.90894)))
("SF_PLANTING" 0 ((13009.04977 237.55656) (12997.73756 233.93382) (12963.80090 233.93382) (12929.86425 248.86878)))
("SF_SOLAR" 0 ((12933.63541 8024.13281) (12937.40532 8031.67421)))
("SF_SOLAR" 0 ((12933.63541 7971.34231) (12933.63541 7986.42534)))
("SF_SOLAR" 0 ((12933.63541 7922.32274) (12933.63541 7929.86425)))
("SF_PLANTING" 0 ((12933.63541 7051.28179) (12934.69186 7036.19910) (12952.48869 7006.03292)))
("SF_PLANTING" 0 ((12933.63541 7051.28179) (12923.52738 7062.59434) (12922.47794 7073.90622) (12948.71753 7106.63857)
(12960.02285 7106.63857) (12966.36799 7100.29502) (12971.34197 7066.36527)))
("SF_PLANTING" 0 ((12933.63541 7051.28179) (12971.34197 7066.36527)))
("SF_PLANTING" 0 ((12963.80090 6949.47183) (12944.94762 6930.77308) (12933.63541 6926.84740)))
("SF_PLANTING" 0 ((12982.65419 399.69740) (12977.68020 418.55204) (12959.88190 441.02873) (12933.63541 456.25848)))
("SF_SOLAR" 0 ((12937.40532 8133.48416) (12944.94762 8122.17195)))
("SF_PLANTING" 0 ((12944.94762 6779.78857) (12937.40532 6779.78857)))
("SF_PLANTING" 0 ((12937.40532 6779.78857) (12937.55995 6749.62319) (12948.71753 6734.53971)))
("SF_MASONRY_AND_ARCH" 0 ((12967.57206 3148.56686) (12937.40532 3152.33812)))
("SF_MASONRY_AND_ARCH" 0 ((13125.94310 3073.15260) (13114.63088 3076.62692) (13088.23529 3073.15882) (12990.19649
3080.69355) (12982.65419 3076.92308) (12937.40532 3076.92308)))
("SF_MASONRY_AND_ARCH" 0 ((12937.40532 1240.57410) (12948.71199 1241.77749) (12963.80781 1255.50147) (13058.06980
1255.65611)))
("SF_PLANTING" 0 ((12963.80090 6949.47183) (12952.34095 6968.17749) (12941.17647 6975.86753)))
("SF_PLANTING" 0 ((12941.17647 6975.86753) (12946.00407 6998.48507) (12952.48869 7006.03292)))
("SF_PLANTING" 0 ((12944.94762 6553.54423) (12941.17647 6542.23201)))
("SF_MASONRY_AND_ARCH" 0 ((13016.59084 1508.29468) (12941.17647 1504.52489)))
("SF_SOLAR" 0 ((12944.94762 7869.53247) (12967.57206 7869.53247)))
("SF_PLANTING" 0 ((12944.94762 6779.78857) (13042.98643 6779.78857)))
("SF_PLANTING" 0 ((12944.94762 6779.78857) (12945.09548 6825.03744) (12960.02975 6858.97410)))
("SF_PLANTING" 0 ((12956.25984 6636.50102) (12948.71753 6640.27149) (12944.94762 6647.81324)))
("SF_PLANTING" 0 ((12944.94762 6553.54423) (12941.17647 6568.62771) (12944.94762 6591.25215)))
("SF_PLANTING" 0 ((12944.94762 6553.54423) (12960.02975 6564.85645)))
("SF_ARCHITECTURE" 0 ((12948.71753 3797.13382) (12971.34197 3793.36391) (12997.73756 3797.13382) (13099.54751
3793.37014) (13118.40079 3797.13382)))
("SF_SOLAR" 0 ((12956.25984 8024.13281) (12952.48869 8031.67421)))
("SF_PLANTING" 0 ((12952.48869 7006.03292) (12978.88428 7002.26244)))
("SF_SOLAR" 0 ((12956.25984 7986.42534) (12956.25984 7971.34231)))
("SF_SOLAR" 0 ((12956.25984 7944.94717) (12956.25984 7952.48869)))
("SF_PLANTING" 0 ((12956.25984 6881.59853) (12960.02975 6858.97410)))
("SF_PLANTING" 0 ((12956.25984 6881.59853) (12963.80781 6892.76324) (13005.27862 6919.30645)))
("SF_ARCHITECTURE" 0 ((12956.25984 5754.14774) (12956.25984 5765.45995)))
("SF_PLANTING" 0 ((12956.25984 716.43948) (12963.80781 720.06369) (13009.04977 720.35916) (13020.36199 723.83416)
(13092.00645 724.12964) (13103.31867 727.45622) (13114.63088 724.12964) (13178.73303 723.98812) (13257.91855 731.37590)
(13280.53609 727.90701) (13288.08405 731.52432)))
("SF_SOLAR" 0 ((13129.71301 8107.08891) (13084.46414 8100.74514) (12960.02975 8103.31833)))
("SF_PLANTING" 0 ((13020.36199 6862.74536) (12990.19649 6855.35192) (12960.02975 6858.97410)))
("SF_PLANTING" 0 ((12993.96640 6949.47183) (12963.80090 6949.47183)))
("SF_PLANTING" 0 ((12967.57206 6576.16867) (12974.05679 6587.48122) (12975.26086 6610.10532) (12979.94072 6621.26968)
(12997.58982 6632.87805) (13005.27862 6644.04197)))
("SF_SOLAR" 0 ((12978.88428 8171.19163) (12971.34197 8171.19163)))
("SF_PLANTING" 0 ((12971.34197 7066.36527) (12992.76222 7032.42862) (12988.99242 7013.57466) (12978.88428 7002.26244)))
("SF_PLANTING" 0 ((12971.34197 6659.12545) (12985.22817 6681.74989) (12987.62952 6711.76776) (13001.50871 6723.22749)))
("SF_SOLAR" 0 ((12978.88428 8073.15226) (12978.88428 8084.46448)))
("SF_SOLAR" 0 ((12978.88428 8024.13281) (12978.88428 8031.67421)))
("SF_SOLAR" 0 ((12978.88428 8001.50837) (12978.88428 8009.04977)))
("SF_SOLAR" 0 ((12978.88428 7944.94717) (12978.88428 7952.48869)))
("SF_PLANTING" 0 ((12993.96640 6949.47183) (12983.71052 6968.32579) (12978.88428 7002.26244)))
("SF_MASONRY_AND_ARCH" 0 ((12982.65419 3408.74785) (12996.53337 3408.44548) (12993.96640 3389.89468)))
("SF_PLANTING" 0 ((13016.59084 825.79186) (12982.65419 822.02206)))
("SF_PLANTING" 0 ((12982.65419 399.69740) (13005.27862 399.54412) (13012.67183 395.77296) (13039.36301 354.60385)
(13046.75758 350.67873)))
("SF_PLANTING" 0 ((12982.65419 399.69740) (12982.65419 392.15781)))
("SF_PLANTING" 0 ((12997.73756 346.90894) (12982.65419 392.15781)))
("SF_SOLAR" 0 ((13148.56753 8141.02557) (13125.94310 8144.79638) (13095.77636 8141.03213) (12986.42534 8141.02557)))
("SF_SOLAR" 0 ((12990.19649 8190.04525) (12990.19649 8197.58665)))
("SF_SOLAR" 0 ((12990.19649 8182.50385) (12990.19649 8171.19163)))
("SF_PLANTING" 0 ((12993.96640 6949.47183) (13005.27862 6949.47183)))
("SF_PLANTING" 0 ((12993.96640 471.34333) (13027.90305 444.94627)))
("SF_SOLAR" 0 ((13001.50871 8133.48416) (13001.50871 8122.17195) (12997.73756 8118.40113)))
("SF_SOLAR" 0 ((12997.73756 7929.86425) (12997.73756 7914.78133)))
("SF_MASONRY_AND_ARCH" 0 ((12997.73756 893.66516) (13009.04977 893.66516)))
("SF_PLANTING" 0 ((12997.73756 346.90894) (13030.47002 309.19966) (13034.24819 290.35271) (13031.67421 282.80543)))
("SF_SOLAR" 0 ((13001.50871 8069.38167) (13001.50871 8084.46448)))
("SF_SOLAR" 0 ((13001.50871 8024.13281) (13001.50871 8031.67421)))
("SF_ARCHITECTURE" 0 ((13076.92308 5622.17195) (13027.90305 5622.32002) (13016.59084 5625.78812) (13001.50871
5622.17195)))
("SF_MASONRY_AND_ARCH" 0 ((13031.67421 3337.10407) (13005.43326 3338.30826) (13001.50871 3348.41629)))
("SF_MASONRY_AND_ARCH" 0 ((13001.50871 3257.91855) (13001.50871 3295.62568)))
("SF_MASONRY_AND_ARCH" 0 ((13001.50871 3257.91855) (13009.04977 3254.14808)))
("SF_SOLAR" 0 ((13005.27862 7850.67873) (13020.36199 7888.38609)))
("SF_PLANTING" 0 ((13005.27862 6949.47183) (13005.27862 6919.30645)))
("SF_PLANTING" 0 ((13020.36199 6957.01357) (13005.27862 6949.47183)))
("SF_PLANTING" 0 ((13012.82093 6911.76471) (13005.27862 6919.30645)))
("SF_ARCHITECTURE" 0 ((13095.77636 5712.66968) (13076.92308 5708.91199) (13061.83971 5712.52161) (13035.44536
5708.91199) (13005.27862 5712.66968)))
("SF_ARCHITECTURE" 0 ((13005.27862 5580.69423) (13024.13314 5584.46414) (13137.25532 5580.70045) (13152.33744
5584.31629) (13223.98190 5584.61256) (13235.29412 5588.23529)))
("SF_PLANTING" 0 ((13016.59084 825.79186) (13012.67319 886.11787) (13009.04977 893.66516)))
("SF_MASONRY_AND_ARCH" 0 ((13009.04977 893.66516) (13012.82093 916.28959)))
("SF_PLANTING" 0 ((13084.46414 252.63857) (13061.83971 233.94005) (13016.59774 233.93382) (13009.04977 237.55656)))
("SF_PLANTING" 0 ((13012.82093 252.63857) (13009.04977 248.86878) (13009.04977 237.55656)))
("SF_PLANTING" 0 ((13012.82093 6911.76471) (13020.21425 6881.59853) (13020.36199 6862.74536)))
("SF_PLANTING" 0 ((13012.82093 6911.76471) (13046.75758 6912.96900) (13092.00645 6942.82545) (13110.85973 6945.70136)))
("SF_MASONRY_AND_ARCH" 0 ((13012.82093 935.14423) (13012.82093 972.85068)))
("SF_ARCHITECTURE" 0 ((13254.14740 4464.55464) (13016.59084 4464.55464)))
("SF_MASONRY_AND_ARCH" 0 ((13035.44536 2631.97613) (13034.24129 2586.72726) (13024.13869 2576.61912) (13016.59084
2575.41505)))
("SF_PLANTING" 0 ((13016.59084 825.79186) (13046.75758 818.24943)))
("SF_PLANTING" 0 ((13020.36199 6957.01357) (13027.90305 6998.49197)))
("SF_PLANTING" 0 ((13020.36199 6957.01357) (13042.98643 6964.55532)))
("SF_PLANTING" 0 ((13020.36199 6862.74536) (13035.51312 6862.52296) (13044.87138 6857.08925)))
("SF_SOLAR" 0 ((13024.13314 8069.38167) (13024.13314 8084.46448)))
("SF_SOLAR" 0 ((13024.13314 8031.67421) (13024.13314 8020.36199)))
("SF_SOLAR" 0 ((13024.13314 7986.42534) (13027.90305 7978.88394)))
("SF_MASONRY_AND_ARCH" 0 ((13024.13314 2450.98066) (13024.13314 2462.29287)))
("SF_MASONRY_AND_ARCH" 0 ((13024.13314 2450.98066) (13034.24129 2439.66844) (13032.87839 2417.05023) (13042.98643
2409.65690) (13144.79638 2406.92964) (13190.04525 2409.49604) (13212.66968 2405.73179) (13288.08405 2409.49604)
(13367.26957 2398.34468) (13381.83654 2406.78122) (13378.58179 2424.58495)))
("SF_MASONRY_AND_ARCH" 0 ((13024.13314 1847.66188) (13031.67421 1870.28631)))
("SF_MASONRY_AND_ARCH" 0 ((13024.13314 1809.95475) (13024.28100 1768.48326) (13027.90305 1760.93609)))
("SF_MASONRY_AND_ARCH" 0 ((13024.13314 1809.95475) (13039.21527 1817.34186) (13163.64966 1821.26697)))
("SF_MASONRY_AND_ARCH" 0 ((13024.13314 1436.65158) (13095.77636 1447.81606) (13125.94310 1444.19887) (13208.89853
1444.19887) (13284.31414 1451.73360) (13314.47964 1447.96380)))
("SF_SOLAR" 0 ((13027.90305 8129.71335) (13031.67421 8118.40113)))
("SF_PLANTING" 0 ((13027.90305 7036.19910) (13050.52749 7028.65735)))
("SF_PLANTING" 0 ((13027.90305 6998.49197) (13024.13314 7013.57466) (13027.90305 7036.19910)))
("SF_PLANTING" 0 ((13050.52749 7081.44796) (13029.10713 7062.59400) (13027.90305 7036.19910)))
("SF_PLANTING" 0 ((13027.90305 6998.49197) (13050.52749 7017.34514)))
("SF_MASONRY_AND_ARCH" 0 ((13027.90305 1021.86934) (13031.67421 999.24491)))
("SF_PLANTING" 0 ((13027.90305 444.94627) (13028.95939 429.86425) (13060.64242 377.07296) (13061.83971 354.44853)))
("SF_PLANTING" 0 ((13137.25532 388.38518) (13104.21357 460.03111) (13095.77081 470.13778) (13084.46414 470.28620)
(13050.52749 449.92229) (13027.90305 444.94627)))
("SF_PLANTING" 0 ((13039.21527 6715.68654) (13031.67421 6734.53971)))
("SF_PLANTING" 0 ((13031.67421 6440.42240) (13028.06459 6429.12330) (13031.67421 6423.82251) (13035.44536 6425.33937)))
("SF_MASONRY_AND_ARCH" 0 ((13190.04525 995.47511) (13046.75758 995.48133) (13031.67421 999.24491)))
("SF_PLANTING" 0 ((13084.46414 252.63857) (13073.15192 262.89514) (13031.67421 282.80543)))
("SF_SOLAR" 0 ((13065.61086 7903.46912) (13035.44536 7903.46912)))
("SF_SOLAR" 0 ((13035.44536 7903.46912) (13028.41391 7913.94559) (13036.50181 7937.40577) (13079.64480 7997.73756)
(13170.14253 8144.79638) (13174.96188 8159.87941)))
("SF_SOLAR" 0 ((13035.44536 7854.44943) (13045.70124 7869.53247) (13047.95486 7884.46075) (13054.29864 7888.38609)))
("SF_PLANTING" 0 ((13035.44536 6515.83710) (13042.98643 6527.14932) (13046.75758 6527.14932)))
("SF_MASONRY_AND_ARCH" 0 ((13035.44536 2631.97613) (13058.06980 2639.36867) (13084.46414 2635.75351) (13125.94310
2639.51708)))
("SF_MASONRY_AND_ARCH" 0 ((13035.44536 2541.47839) (13039.21527 2526.39491)))
("SF_SOLAR" 0 ((13159.87975 7839.36652) (13039.21527 7839.36652)))
("SF_PLANTING" 0 ((13073.15192 6708.14480) (13072.09548 6696.83258) (13065.46312 6685.67523) (13046.75758 6681.90430)
(13035.60011 6693.06210) (13039.21527 6715.68654)))
("SF_PLANTING" 0 ((13039.21527 6715.68654) (13065.61086 6725.11312)))
("SF_MASONRY_AND_ARCH" 0 ((13054.29864 2526.39491) (13039.21527 2526.39491)))
("SF_PLANTING" 0 ((13058.06980 6779.78857) (13042.98643 6779.78857)))
("SF_PLANTING" 0 ((13065.61086 6745.85192) (13050.53439 6750.67919) (13044.19061 6757.17070) (13042.98643 6779.78857)))
("SF_MASONRY_AND_ARCH" 0 ((13042.98643 2092.76018) (13040.56708 2100.30814) (13054.29864 2111.45950) (13129.71301
2111.76188) (13141.02523 2115.22998) (13182.50419 2111.62036) (13205.12862 2115.38462) (13295.62636 2115.37839)
(13310.70848 2111.61414)))
("SF_MASONRY_AND_ARCH" 0 ((13118.40079 2009.80419) (13103.31867 2020.05995) (13080.69423 2021.26414) (13054.30554
2029.85532) (13042.98643 2043.74084)))
("SF_PLANTING" 0 ((13046.75758 6847.66188) (13050.52749 6851.43314) (13044.87138 6857.08925)))
("SF_PLANTING" 0 ((13044.87138 6857.08925) (13046.75758 6847.66188)))
("SF_PLANTING" 0 ((13046.75758 6847.66188) (13042.98643 6851.43314) (13044.87138 6857.08925)))
("SF_PLANTING" 0 ((13044.87138 6857.08925) (13061.83971 6869.08880) (13080.69423 6870.28631)))
("SF_SOLAR" 0 ((13046.75758 8069.38167) (13046.75758 8076.92308)))
("SF_PLANTING" 0 ((13046.75758 6847.66188) (13047.81403 6832.57919) (13057.92206 6806.18428) (13058.06980 6779.78857)))
("SF_PLANTING" 0 ((13046.75758 6527.14932) (13046.75758 6534.69106)))
("SF_PLANTING" 0 ((13046.75758 6527.14932) (13076.92308 6519.60758)))
("SF_PLANTING" 0 ((13107.08857 3337.10407) (13046.75758 3337.10407)))
("SF_PLANTING" 0 ((13046.75758 350.67873) (13058.06980 350.67873) (13061.83971 354.44853)))
("SF_PLANTING" 0 ((13076.92308 324.28450) (13065.61086 325.34016) (13054.44638 331.97251) (13046.75758 350.67873)))
("SF_PLANTING" 0 ((13050.52749 7017.34514) (13050.52749 7028.65735)))
("SF_PLANTING" 0 ((13084.46414 7058.82353) (13050.52749 7028.65735)))
("SF_PLANTING" 0 ((13050.52749 7017.34514) (13061.83416 7009.79762) (13069.38201 6998.49197)))
("SF_MASONRY_AND_ARCH" 0 ((13054.29864 2714.93213) (13054.29864 2733.78609)))
("SF_MASONRY_AND_ARCH" 0 ((13137.25532 2730.01482) (13129.70611 2741.17240) (13122.17195 2744.94367) (13073.15192
2741.17930) (13054.29864 2733.78609)))
("SF_PLANTING" 0 ((13058.06980 6979.63801) (13069.38201 6998.49197)))
("SF_PLANTING" 0 ((13078.80803 6774.13247) (13069.44977 6779.56686) (13058.06980 6779.78857)))
("SF_MASONRY_AND_ARCH" 0 ((13058.06980 1508.29468) (13065.61086 1519.60690)))
("SF_MASONRY_AND_ARCH" 0 ((13076.92308 1240.57410) (13065.61776 1244.49853) (13058.06980 1255.65611)))
("SF_MASONRY_AND_ARCH" 0 ((13058.06980 1255.65611) (13069.38201 1265.77036) (13080.69423 1269.68937) (13125.94310
1272.25645) (13136.05124 1263.20339) (13137.25532 1255.65611)))
("SF_PLANTING" 0 ((13076.92308 324.28450) (13071.94774 346.90136) (13061.83971 354.44853)))
("SF_SOLAR" 0 ((13069.38201 8031.67421) (13065.61086 8024.13281)))
("SF_SOLAR" 0 ((13065.61086 7903.46912) (13073.15882 7899.85294) (13092.00645 7903.46912) (13299.39627 7903.46912)
(13306.93857 7903.46912) (13325.79186 7903.46912) (13657.61731 7903.46912) (13691.55396 7899.70486) (13710.40724
7903.46256) (13834.84163 7903.62376) (13849.92500 7911.01052)))
("SF_SOLAR" 0 ((13065.61086 7903.46912) (13070.43846 7918.55204) (13230.32568 8171.19163) (13235.29412 8193.81606)))
("SF_PLANTING" 0 ((13065.61086 6745.85192) (13065.61086 6725.11312)))
("SF_PLANTING" 0 ((13078.80803 6774.13247) (13073.22647 6768.39593) (13065.61086 6745.85192)))
("SF_PLANTING" 0 ((13073.15192 6708.14480) (13065.61086 6725.11312)))
("SF_PLANTING" 0 ((13065.61086 6725.11312) (13088.23529 6726.99876)))
("SF_PLANTING" 0 ((13069.38201 6312.21719) (13054.45328 6293.36357) (13055.50283 6282.05792) (13065.61086 6274.50973)))
("SF_MASONRY_AND_ARCH" 0 ((13288.08405 2541.47839) (13276.77183 2530.32081) (13208.89853 2530.01844) (13190.04525
2526.39491) (13167.42081 2530.15995) (13103.31867 2526.39491) (13065.61086 2530.16618)))
("SF_SOLAR" 0 ((13069.38201 8118.40113) (13069.38201 8133.48416)))
("SF_SOLAR" 0 ((13069.38201 8069.38167) (13069.38201 8084.46448)))
("SF_PLANTING" 0 ((13069.38201 6998.49197) (13084.46414 6998.49197)))
("SF_PLANTING" 0 ((13069.38201 6610.10532) (13069.38201 6576.16867)))
("SF_PLANTING" 0 ((13076.92308 6640.27149) (13058.07534 6637.39559) (13047.82093 6625.18846) (13047.96867 6617.65362)
(13054.30554 6611.30962) (13069.38201 6610.10532)))
("SF_PLANTING" 0 ((13076.92308 6640.27149) (13084.30249 6621.41787) (13080.53959 6614.03100) (13069.38201 6610.10532)))
("SF_PLANTING" 0 ((13069.38201 6576.16867) (13069.53676 6553.54423) (13076.76844 6538.46154) (13076.92308 6519.60758)))
("SF_PLANTING" 0 ((13122.17195 6553.54423) (13103.31867 6571.34219) (13088.23529 6578.88314) (13069.38201 6576.16867)))
("SF_PLANTING" 0 ((13069.38201 6478.12964) (13073.51369 6437.02025) (13103.16957 6428.95554) (13118.40079 6402.71493)))
("SF_PLANTING" 0 ((13069.38201 6478.12964) (13080.69423 6481.90045)))
("SF_PLANTING" 0 ((13069.38201 6312.21719) (13073.15192 6331.07081) (13073.00407 6376.31968) (13069.53676 6387.63190)
(13072.85633 6402.71493) (13069.38201 6414.02715)))
("SF_PLANTING" 0 ((13069.38201 6312.21719) (13083.40215 6300.89842) (13084.46414 6285.82195)))
("SF_MASONRY_AND_ARCH" 0 ((13069.38201 2865.76143) (13069.53676 2843.13699) (13076.92998 2831.97941) (13125.93620
2823.07964) (13141.02523 2797.88812)))
("SF_PLANTING" 0 ((13073.15192 6708.14480) (13087.03111 6715.83405) (13088.23529 6726.99876)))
("SF_PLANTING" 0 ((13073.15192 6240.57308) (13073.15192 6217.94864)))
("SF_MASONRY_AND_ARCH" 0 ((13190.04525 3186.27477) (13110.85973 3186.26855) (13088.23529 3182.50351) (13073.15192
3186.27477)))
("SF_MASONRY_AND_ARCH" 0 ((13280.54299 1553.54355) (13084.46414 1553.69887) (13074.50373 1561.09287) (13073.15192
1579.94061)))
("SF_PLANTING" 0 ((13080.69423 6659.12545) (13076.92308 6640.27149)))
("SF_PLANTING" 0 ((13076.92308 6519.60758) (13080.69423 6481.90045)))
("SF_PLANTING" 0 ((13076.92308 3284.31346) (13084.47104 3287.93699) (13174.96188 3288.08473)))
("SF_PLANTING" 0 ((13099.54751 369.53337) (13076.92308 418.55204)))
("SF_PLANTING" 0 ((13076.92308 324.28450) (13094.57907 297.88744) (13100.74887 275.26097) (13112.74468 262.06731)))
("SF_PLANTING" 0 ((13078.80803 6774.13247) (13086.96346 6764.77342) (13095.77636 6734.53971)))
("SF_PLANTING" 0 ((13078.80803 6774.13247) (13099.54751 6783.55984)))
("SF_PLANTING" 0 ((13103.31867 6855.20362) (13088.38303 6860.17183) (13080.69423 6870.28631)))
("SF_PLANTING" 0 ((13118.40079 6881.59853) (13110.85283 6888.98541) (13095.77636 6887.93597) (13080.69423 6870.28631)))
("SF_PLANTING" 0 ((13080.69423 6481.90045) (13099.54751 6478.13620) (13141.02523 6481.90045) (13163.64966 6478.13620)
(13344.64559 6478.12964)))
("SF_PLANTING" 0 ((13099.54751 7058.82353) (13084.46414 7058.82353)))
("SF_PLANTING" 0 ((13084.46414 7058.82353) (13084.61188 7085.21844) (13089.43247 7100.30192) (13110.85973 7119.15509)))
("SF_PLANTING" 0 ((13099.54751 6998.49197) (13084.46414 6998.49197)))
("SF_PLANTING" 0 ((13099.54751 7047.51131) (13089.28473 7028.65735) (13084.46414 6998.49197)))
("SF_PLANTING" 0 ((13084.46414 252.63857) (13099.55023 253.84061) (13112.74468 262.06731)))
("SF_PLANTING" 0 ((13095.77636 6734.53971) (13088.23529 6726.99876)))
("SF_MASONRY_AND_ARCH" 0 ((13088.23529 1862.74514) (13095.77636 1862.74514)))
("SF_MASONRY_AND_ARCH" 0 ((13088.23529 1651.58371) (13088.23529 1644.04129)))
("SF_MASONRY_AND_ARCH" 0 ((13114.63088 1606.33484) (13088.23529 1606.33484)))
("SF_PLANTING" 0 ((13137.25532 550.52885) (13118.40079 549.47172) (13088.23529 535.44400)))
("SF_SOLAR" 0 ((13092.00645 8133.48416) (13092.00645 8118.40113)))
("SF_SOLAR" 0 ((13092.00645 8069.38167) (13092.00645 8084.46448)))
("SF_SOLAR" 0 ((13095.77636 7937.40577) (13310.70848 7937.40577)))
("SF_PLANTING" 0 ((13122.17195 6736.42534) (13095.77636 6734.53971)))
("SF_SOLAR" 0 ((13099.54751 8009.04977) (13110.85973 8001.50837)))
("SF_PLANTING" 0 ((13099.54751 7058.82353) (13099.54751 7047.51131)))
("SF_PLANTING" 0 ((13099.54751 7058.82353) (13122.17885 7073.59706) (13133.48416 7066.36527)))
("SF_PLANTING" 0 ((13114.63088 7036.19910) (13099.54751 7047.51131)))
("SF_PLANTING" 0 ((13110.85973 6972.09627) (13104.51595 6976.02195) (13099.54751 6998.49197)))
("SF_PLANTING" 0 ((13099.54751 6998.49197) (13110.85973 7006.03292)))
("SF_PLANTING" 0 ((13122.17195 6783.55984) (13099.54751 6783.55984)))
("SF_PLANTING" 0 ((13099.54751 6783.55984) (13095.92410 6794.87206) (13095.92410 6828.80871) (13103.31867 6847.66188)))
("SF_PLANTING" 0 ((13099.54751 369.53337) (13133.48416 369.53337)))
("SF_PLANTING" 0 ((13099.54751 369.53337) (13103.31867 354.44853)))
("SF_PLANTING" 0 ((13103.31867 6855.20362) (13103.31867 6847.66188)))
("SF_PLANTING" 0 ((13118.40079 6881.59853) (13113.42681 6866.51584) (13103.31867 6855.20362)))
("SF_PLANTING" 0 ((13144.79638 6847.66188) (13103.31867 6847.66188)))
("SF_PLANTING" 0 ((13125.94310 6700.60305) (13103.31867 6689.29084)))
("SF_PLANTING" 0 ((13103.31867 3525.64129) (13110.86663 3531.98439) (13137.25532 3536.80577) (13182.50419 3536.95351)))
("SF_MASONRY_AND_ARCH" 0 ((13107.08857 1862.74514) (13186.27410 1862.74514) (13205.12862 1862.74514) (13401.20622
1862.74514)))
("SF_PLANTING" 0 ((13129.71301 6994.72070) (13110.85973 7006.03292)))
("SF_PLANTING" 0 ((13114.63088 7036.19910) (13114.48314 7013.58122) (13110.85973 7006.03292)))
("SF_PLANTING" 0 ((13110.85973 6972.09627) (13110.85973 6945.70136)))
("SF_PLANTING" 0 ((13129.71301 6994.72070) (13122.02421 6979.64457) (13110.85973 6972.09627)))
("SF_PLANTING" 0 ((13152.33744 6938.15962) (13110.85973 6945.70136)))
("SF_MASONRY_AND_ARCH" 0 ((13122.17195 1185.89649) (13110.85973 1187.78281)))
("SF_PLANTING" 0 ((13112.74468 262.06731) (13129.71301 246.30238) (13167.42081 245.09898)))
("SF_PLANTING" 0 ((13148.56753 312.97229) (13143.59219 294.11765) (13112.74468 262.06731)))
("SF_SOLAR" 0 ((13114.63088 7971.34231) (13329.56301 7971.34231)))
("SF_SOLAR" 0 ((13114.63088 7914.78133) (13114.63088 7926.09355)))
("SF_PLANTING" 0 ((13125.94310 7043.74084) (13114.63088 7036.19910)))
("SF_PLANTING" 0 ((13114.63088 6659.12545) (13122.17195 6662.89593)))
("SF_MASONRY_AND_ARCH" 0 ((13401.20622 1964.55532) (13306.93857 1964.54910) (13284.31414 1960.78405) (13246.60633
1964.40068) (13174.96188 1957.30973) (13159.87975 1960.77783) (13125.94310 1958.36618) (13115.83507 1968.31957)
(13114.63088 1975.86753)))
("SF_MASONRY_AND_ARCH" 0 ((13114.63088 1104.82658) (13129.71301 1104.82658) (13171.19197 1104.82658) (13205.12862
1104.82658) (13216.44084 1104.82658)))
("SF_MASONRY_AND_ARCH" 0 ((13114.63088 1104.82658) (13114.63088 1089.74265)))
("SF_SOLAR" 0 ((13122.17195 8133.48416) (13122.17195 8122.17195) (13118.40079 8118.40113)))
("SF_PLANTING" 0 ((13118.40079 6881.59853) (13136.19898 6873.90271) (13144.79638 6847.66188)))
("SF_PLANTING" 0 ((13118.40079 3797.13382) (13133.48416 3793.36391) (13190.04525 3797.13382)))
("SF_PLANTING" 0 ((13118.40079 3797.13382) (13129.71301 3827.30057)))
("SF_MASONRY_AND_ARCH" 0 ((13122.17195 1185.89649) (13118.40079 1138.76414)))
("SF_PLANTING" 0 ((13122.17195 6783.55984) (13129.71301 6783.55984)))
("SF_PLANTING" 0 ((13122.17195 6783.55984) (13122.17195 6736.42534)))
("SF_PLANTING" 0 ((13125.94310 6700.60305) (13122.17195 6736.42534)))
("SF_PLANTING" 0 ((13122.17195 6736.42534) (13144.79638 6738.31097)))
("SF_MASONRY_AND_ARCH" 0 ((13122.17195 2982.65486) (13152.33744 2975.11312) (13163.64276 2976.31109) (13171.19197
2982.65486)))
("SF_MASONRY_AND_ARCH" 0 ((13122.17195 2941.17647) (13125.94310 2948.71821)))
("SF_MASONRY_AND_ARCH" 0 ((13137.25532 2730.01482) (13133.32952 2718.70950) (13122.17195 2711.16165)))
("SF_MASONRY_AND_ARCH" 0 ((13122.17195 1185.89649) (13129.71301 1184.01301)))
("SF_MASONRY_AND_ARCH" 0 ((13122.17195 1185.89649) (13137.25532 1255.65611)))
("SF_PLANTING" 0 ((13125.94310 6700.60305) (13129.41742 6693.05554) (13125.94310 6681.74989)))
("SF_PLANTING" 0 ((13125.94310 6640.27149) (13137.25532 6610.10532)))
("SF_MASONRY_AND_ARCH" 0 ((13129.71301 3031.67421) (13126.09095 3039.22217) (13125.94310 3073.15260)))
("SF_MASONRY_AND_ARCH" 0 ((13125.94310 3073.15260) (13144.79638 3076.92308) (13178.73303 3076.77534) (13190.04525
3073.15260)))
("SF_MASONRY_AND_ARCH" 0 ((13125.94310 2665.91278) (13125.94310 2639.51708)))
("SF_MASONRY_AND_ARCH" 0 ((13125.94310 2639.51708) (13152.33744 2635.75283) (13242.83518 2635.74661)))
("SF_PLANTING" 0 ((13284.31414 795.62500) (13223.98190 795.47794) (13197.58631 788.09027) (13133.49106 791.70057)
(13125.94310 784.31278)))
("SF_PLANTING" 0 ((13125.94310 682.50283) (13129.71301 686.27545) (13133.48416 682.50283)))
("SF_PLANTING" 0 ((13129.71301 6994.72070) (13197.58631 7069.98744) (13231.52296 7091.70419) (13253.98722 7095.31980)
(13256.71437 7088.98281) (13249.32115 7066.36527) (13223.98190 7043.74084)))
("SF_PLANTING" 0 ((13205.12862 6783.55984) (13129.71301 6783.55984)))
("SF_PLANTING" 0 ((13154.22364 6838.23529) (13142.22240 6821.26697) (13129.71301 6783.55984)))
("SF_MASONRY_AND_ARCH" 0 ((13129.71301 2779.03495) (13141.02523 2797.88812)))
("SF_MASONRY_AND_ARCH" 0 ((13159.87975 1753.39367) (13133.48416 1753.39367)))
("SF_MASONRY_AND_ARCH" 0 ((13133.48416 1308.44740) (13134.68835 1331.06425) (13152.33744 1341.33314) (13212.66968
1342.37715) (13227.75305 1338.61143)))
("SF_PLANTING" 0 ((13141.02523 354.44853) (13134.68133 358.37443) (13133.48416 369.53337)))
("SF_PLANTING" 0 ((13137.25532 388.38518) (13133.48416 369.53337)))
("SF_SOLAR" 0 ((13137.25532 7948.71799) (13137.25532 7960.03020)))
("SF_MASONRY_AND_ARCH" 0 ((13137.25532 2730.01482) (13235.29412 2730.00860) (13250.37749 2726.24434)))
("SF_MASONRY_AND_ARCH" 0 ((13137.25532 2319.00452) (13137.25532 2285.06787)))
("SF_MASONRY_AND_ARCH" 0 ((13137.25532 2319.00452) (13280.54299 2319.15226) (13333.33292 2326.39163) (13386.12410
2315.24027) (13412.51844 2318.99830) (13616.13835 2315.23405) (13650.07500 2319.00452)))
("SF_MASONRY_AND_ARCH" 0 ((13137.25532 2156.86301) (13133.48416 2160.63348) (13137.25532 2168.17523)))
("SF_MASONRY_AND_ARCH" 0 ((13137.25532 1606.33484) (13310.70848 1606.32862) (13340.87523 1602.56505)))
("SF_MASONRY_AND_ARCH" 0 ((13137.25532 1255.65611) (13156.10860 1259.27885) (13220.21075 1259.42104) (13239.06527
1251.88631)))
("SF_PLANTING" 0 ((13137.25532 388.38518) (13161.76471 390.27149)))
("SF_SOLAR" 0 ((13141.02523 8005.27896) (13216.44084 8012.81403) (13355.95735 8012.81403) (13367.26957 8009.04977)))
("SF_PLANTING" 0 ((13141.02523 3834.84163) (13148.56753 3834.84163)))
("SF_PLANTING" 0 ((13141.02523 3337.10407) (13152.33744 3340.87455)))
("SF_MASONRY_AND_ARCH" 0 ((13141.02523 2797.88812) (13190.04525 2812.82387) (13223.98190 2809.20034)))
("SF_MASONRY_AND_ARCH" 0 ((13141.02523 2194.57014) (13148.57308 2198.04446) (13159.87975 2194.57014)))
("SF_MASONRY_AND_ARCH" 0 ((13141.02523 1670.43835) (13306.93857 1670.43145) (13329.56301 1666.66572) (13386.12410
1670.43145) (13401.20622 1666.66572)))
("SF_PLANTING" 0 ((13141.02523 354.44853) (13141.17296 331.82410) (13148.56753 312.97229)))
("SF_PLANTING" 0 ((13141.02523 354.44853) (13155.05226 365.76833) (13161.76471 390.27149)))
("SF_PLANTING" 0 ((13148.56753 6843.89140) (13148.56753 6847.66188) (13144.79638 6847.66188)))
("SF_PLANTING" 0 ((13148.56753 6843.89140) (13144.79638 6847.66188)))
("SF_PLANTING" 0 ((13148.56753 6843.89140) (13152.33744 6843.89140) (13154.22364 6838.23529)))
("SF_PLANTING" 0 ((13148.56753 6843.89140) (13148.56753 6840.12093) (13154.22364 6838.23529)))
("SF_PLANTING" 0 ((13148.56753 312.97229) (13171.19197 317.94695) (13190.04525 334.39186) (13201.35747 335.59672)))
("SF_PLANTING" 0 ((13152.33744 6938.15962) (13157.16493 6923.07692) (13188.85351 6885.36980) (13200.23337 6851.36550)
(13199.47251 6842.00577)))
("SF_PLANTING" 0 ((13174.96188 6941.93088) (13152.33744 6938.15962)))
("SF_PLANTING" 0 ((13171.19197 3887.63156) (13152.33744 3880.09050)))
("SF_PLANTING" 0 ((13154.22364 6838.23529) (13199.47251 6842.00577)))
("SF_SOLAR" 0 ((13156.10860 8174.96222) (13156.10860 8182.50385)))
("SF_SOLAR" 0 ((13156.10860 7982.65452) (13159.87975 7990.19615)))
("SF_PLANTING" 0 ((13174.96188 3472.85068) (13156.10860 3472.85068)))
("SF_ARCHITECTURE" 0 ((13159.87975 5735.29412) (13208.89853 5731.52986) (13386.12410 5731.36855) (13393.65826
5727.59808) (13401.20622 5716.44050)))
("SF_ARCHITECTURE" 0 ((13322.02070 5701.35747) (13310.70848 5705.12172) (13167.42081 5705.28303) (13157.31968
5712.67624) (13159.87975 5735.29412)))
("SF_ARCHITECTURE" 0 ((13159.87975 5735.29412) (13164.70600 5757.91855) (13182.50419 5784.31380)))
("SF_PLANTING" 0 ((13159.87975 3744.34389) (13171.19197 3754.45192) (13182.50419 3755.65611)))
("SF_PLANTING" 0 ((13205.12862 467.57070) (13190.05215 459.88269) (13168.47715 426.09446) (13161.76471 390.27149)))
("SF_PLANTING" 0 ((13205.12862 365.76075) (13200.16029 380.83801) (13193.80950 387.18801) (13178.73303 392.00939)
(13161.76471 390.27149)))
("SF_SOLAR" 0 ((13167.42081 8042.98643) (13322.02070 8042.98643)))
("SF_PLANTING" 0 ((13167.42081 245.09898) (13174.96878 236.66176) (13190.04525 233.78676) (13231.52296 233.94005)
(13250.37749 245.09898)))
("SF_PLANTING" 0 ((13167.42081 245.09898) (13181.44785 271.49321) (13182.50419 282.80543)))
("SF_PLANTING" 0 ((13171.19197 3887.63156) (13186.27410 3877.37602) (13201.35747 3876.31934)))
("SF_PLANTING" 0 ((13171.19197 3887.63156) (13186.27410 3906.48609)))
("SF_PLANTING" 0 ((13171.19197 629.71437) (13280.54299 629.71437)))
("SF_SOLAR" 0 ((13174.96188 8159.87941) (13205.12862 8193.81606)))
("SF_SOLAR" 0 ((13174.96188 8065.61086) (13193.81640 8058.07602) (13371.04072 8058.07602) (13393.66516 8061.84005)))
("SF_PLANTING" 0 ((13174.96188 6941.93088) (13197.58631 6930.76652) (13216.44084 6931.81618) (13235.29412 6941.78235)
(13257.91855 6934.38914)))
("SF_PLANTING" 0 ((13174.96188 6941.93088) (13178.88767 6953.24310) (13205.12862 6979.63801)))
("SF_PLANTING" 0 ((13174.96188 3589.74333) (13182.51109 3586.12059) (13235.29412 3585.97285)))
("SF_PLANTING" 0 ((13174.96188 3589.74333) (13179.78247 3631.22172) (13202.55464 3672.69321) (13216.44084 3682.95554)
(13235.29412 3684.01165)))
("SF_SOLAR" 0 ((13261.68971 7839.36652) (13178.73303 7839.36652)))
("SF_PLANTING" 0 ((13178.73303 6738.31097) (13265.45962 6738.30441) (13288.08405 6734.53971) (13348.41629 6738.31097)))
("SF_ARCHITECTURE" 0 ((15999.24774 5848.41629) (13178.73303 5848.41629)))
("SF_ARCHITECTURE" 0 ((13178.73303 5848.41629) (13161.08394 5825.79186) (13160.03450 5806.93824) (13163.80430
5799.40317) (13182.50419 5784.31380)))
("SF_ARCHITECTURE" 0 ((13178.73303 5848.41629) (13157.16493 5874.81154) (13157.31278 5908.74163) (13174.96188
5919.91233) (13205.12862 5920.06041)))
("SF_MASONRY_AND_ARCH" 0 ((13190.04525 2462.29287) (13182.50419 2466.06335) (13178.73303 2462.29287)))
("SF_SOLAR" 0 ((13182.50419 8020.36199) (13182.50419 8035.44502)))
("SF_SOLAR" 0 ((13182.50419 7990.19615) (13182.50419 7982.65452)))
("SF_SOLAR" 0 ((13182.50419 7956.25939) (13182.50419 7948.71799)))
("SF_ARCHITECTURE" 0 ((13182.50419 5784.31380) (13239.06527 5780.54299) (13276.77183 5784.31380) (13329.56301
5780.54299) (13363.49966 5784.31380) (15901.20475 5788.08450) (15927.60181 5780.54299) (16006.78733 5784.31380)))
("SF_ARCHITECTURE" 0 ((13182.50419 5622.17195) (13208.89853 5625.94276)))
("SF_PLANTING" 0 ((13182.50419 3827.30057) (13201.35747 3834.68699) (13220.21075 3823.52941)))
("SF_PLANTING" 0 ((13182.50419 3755.65611) (13201.35747 3729.26052)))
("SF_PLANTING" 0 ((13182.50419 3755.65611) (13190.04525 3797.13382)))
("SF_PLANTING" 0 ((13220.21075 3804.67613) (13190.04525 3797.13382)))
("SF_MASONRY_AND_ARCH" 0 ((13190.04525 2198.34061) (13310.70848 2198.34683) (13325.79186 2201.95724) (13371.04072
2198.34683) (13389.89400 2202.11188)))
("SF_MASONRY_AND_ARCH" 0 ((13205.12862 1817.49717) (13193.81640 1821.26697)))
("SF_SOLAR" 0 ((13423.83066 8107.08891) (13401.20622 8099.69548) (13325.79186 8099.55407) (13303.16742 8103.31165)
(13280.54299 8099.54751) (13273.00192 8103.31833) (13242.83518 8099.56063) (13216.44084 8103.17025) (13197.58631
8099.54751)))
("SF_PLANTING" 0 ((13197.58631 3721.71946) (13201.35747 3729.26052)))
("SF_PLANTING" 0 ((13199.47251 6842.00577) (13205.12862 6783.55984)))
("SF_PLANTING" 0 ((13212.66968 6843.89140) (13199.47251 6842.00577)))
("SF_PLANTING" 0 ((13235.29412 3725.49061) (13201.35747 3729.26052)))
("SF_MASONRY_AND_ARCH" 0 ((13201.35747 942.68382) (13205.12172 927.60181) (13205.12862 837.10407)))
("SF_PLANTING" 0 ((13201.35747 335.59672) (13239.06527 321.56278) (13257.91855 320.51188)))
("SF_PLANTING" 0 ((13201.35747 335.59672) (13205.12862 365.76075)))
("SF_SOLAR" 0 ((13205.12862 8069.38167) (13208.89853 8084.46448)))
("SF_SOLAR" 0 ((13205.12862 8035.44502) (13205.12862 8020.36199)))
("SF_SOLAR" 0 ((13205.12862 7948.71799) (13205.12862 7960.03020)))
("SF_PLANTING" 0 ((13205.12862 6979.63801) (13205.12862 6994.72070)))
("SF_PLANTING" 0 ((13205.12862 6979.63801) (13242.83518 6991.99966) (13303.16742 7031.23744) (13359.72851 7051.28179)))
("SF_PLANTING" 0 ((13205.12862 6783.55984) (13231.52296 6779.94344) (13246.60633 6783.41154) (13325.79186 6783.55328)
(13344.64514 6779.80170) (13359.72851 6783.41154) (13416.28959 6783.55328) (13431.37296 6779.78857)))
("SF_ARCHITECTURE" 0 ((13205.12862 5920.06041) (13223.98190 5916.28959) (13265.45962 5916.28959) (13378.58179
5916.28959) (13401.20622 5916.28959) (13544.49514 5916.28959) (13567.11957 5916.28959) (13616.13835 5916.28959)
(13759.42726 5916.28959) (13782.05170 5916.28959) (14000.75373 5916.28959) (14023.37817 5916.28959) (15916.28959
5920.06041) (15953.99887 5916.28959) (15976.62330 5923.83100)))
("SF_ARCHITECTURE" 0 ((13344.64559 6048.26538) (13343.58869 6036.95317) (13336.95633 6026.69729) (13212.82432
5942.53676) (13205.12862 5920.06041)))
("SF_MASONRY_AND_ARCH" 0 ((13223.98190 1745.85124) (13209.05317 1750.82104) (13205.12862 1760.93609)))
("SF_PLANTING" 0 ((13205.12862 467.57070) (13208.89853 448.71889) (13205.12862 422.32183)))
("SF_PLANTING" 0 ((13205.12862 467.57070) (13209.94796 493.96776) (13227.75305 535.44400)))
("SF_PLANTING" 0 ((13242.83518 373.30317) (13205.12862 365.76075)))
("SF_PLANTING" 0 ((13212.66968 7028.65735) (13223.98190 7043.74084)))
("SF_PLANTING" 0 ((13212.66968 6843.89140) (13223.98190 6830.01301) (13239.06527 6825.03744)))
("SF_PLANTING" 0 ((13212.66968 6843.89140) (13223.98190 6851.27828) (13276.77183 6855.20362)))
("SF_PLANTING" 0 ((13216.44084 7055.05305) (13223.98190 7043.74084)))
("SF_PLANTING" 0 ((13220.21075 3804.67613) (13220.21075 3823.52941)))
("SF_PLANTING" 0 ((13291.85520 3834.84163) (13276.77183 3842.22873) (13250.37749 3842.22873) (13220.21075 3823.52941)))
("SF_PLANTING" 0 ((13220.21075 3804.67613) (13242.83518 3797.13382)))
("SF_SOLAR" 0 ((13223.98190 8144.79638) (13242.83518 8141.03213) (13446.45509 8141.02557)))
("SF_PLANTING" 0 ((13288.08405 3910.25600) (13250.37749 3910.41097) (13223.98190 3925.33937)))
("SF_SOLAR" 0 ((13227.75305 8020.36199) (13227.75305 8035.44502)))
("SF_PLANTING" 0 ((13257.91855 3876.31934) (13235.30102 3876.17149) (13227.75305 3872.54943)))
("SF_SOLAR" 0 ((13242.83518 8133.48416) (13231.52296 8118.40113)))
("SF_SOLAR" 0 ((13461.53846 8163.65000) (13235.29412 8163.65000)))
("SF_PLANTING" 0 ((13235.29412 6911.76471) (13276.77183 6866.51584)))
("SF_PLANTING" 0 ((13235.29412 3684.01165) (13235.29412 3725.49061)))
("SF_PLANTING" 0 ((13242.83518 3797.13382) (13235.29412 3725.49061)))
("SF_PLANTING" 0 ((13235.29412 3684.01165) (13235.29412 3585.97285)))
("SF_PLANTING" 0 ((13250.37749 3235.29412) (13235.44876 3254.14808) (13235.29412 3585.97285)))
("SF_PLANTING" 0 ((13235.29412 1244.34389) (13239.06527 1251.88631)))
("SF_PLANTING" 0 ((13397.43631 1255.65611) (13378.58179 1251.89118) (13239.06527 1251.88631)))
("SF_PLANTING" 0 ((13291.85520 3808.44604) (13269.23077 3797.28224) (13242.83518 3797.13382)))
("SF_PLANTING" 0 ((13242.83518 388.38518) (13242.83518 373.30317)))
("SF_PLANTING" 0 ((13242.83518 388.38518) (13229.32455 402.63314) (13254.30204 444.79921) (13284.31414 459.88269)
(13295.62636 458.97398) (13314.47964 448.71889)))
("SF_PLANTING" 0 ((13242.83518 388.38518) (13276.77183 399.69740)))
("SF_PLANTING" 0 ((13242.83518 373.30317) (13261.68971 354.44853)))
("SF_SOLAR" 0 ((13246.60633 8227.75271) (13250.37749 8220.21109)))
("SF_PLANTING" 0 ((13246.60633 3955.50486) (13261.68971 3959.27602)))
("SF_MASONRY_AND_ARCH" 0 ((13276.77183 1346.15385) (13269.22387 1342.53111) (13246.60633 1342.38405)))
("SF_PLANTING" 0 ((13295.62636 995.47511) (13246.60633 991.70532)))
("SF_SOLAR" 0 ((13250.37749 8084.46448) (13250.37749 8076.92308)))
("SF_SOLAR" 0 ((13250.37749 8035.44502) (13250.37749 8024.13281)))
("SF_SOLAR" 0 ((13250.37749 7960.03020) (13250.37749 7952.48869)))
("SF_SOLAR" 0 ((13250.37749 7922.32274) (13250.37749 7929.86425)))
("SF_MASONRY_AND_ARCH" 0 ((13250.37749 2960.03043) (13250.37749 3235.29412)))
("SF_PLANTING" 0 ((13299.39627 3239.06459) (13261.68971 3238.91686) (13250.37749 3235.29412)))
("SF_MASONRY_AND_ARCH" 0 ((13250.37749 2960.03043) (13273.00192 2956.25916) (13299.39627 2960.03043)))
("SF_MASONRY_AND_ARCH" 0 ((13250.37749 2960.03043) (13225.03824 2952.33405) (13220.35848 2941.17647) (13221.26018
2907.23982) (13227.90781 2892.30486) (13254.14740 2879.78846) (13271.94559 2861.99095) (13299.24842 2794.11765)
(13304.37161 2718.70260) (13314.47964 2708.59457) (13382.35294 2711.16143) (13397.43631 2711.16143) (15309.20249
2711.16143) (15331.82692 2711.16143) (15659.88122 2711.16143) (15678.73303 2711.16143) (15874.81335 2707.53891)
(15885.96946 2712.21799) (15889.73925 2718.70950) (15894.72149 2809.20034) (15931.52081 2865.76143) (15960.33428
2892.16335) (15968.91787 2944.94695) (15961.53156 2956.10452) (15950.22624 2960.03043)))
("SF_MASONRY_AND_ARCH" 0 ((13397.43631 1745.85124) (13306.93857 1745.70351) (13291.85520 1740.41753) (13250.37749
1742.08145)))
("SF_PLANTING" 0 ((13250.37749 245.09898) (13261.68971 237.71120) (13306.93857 237.55656)))
("SF_PLANTING" 0 ((13257.91855 320.51188) (13250.37749 245.09898)))
("SF_SOLAR" 0 ((13257.91855 7888.38609) (13257.91855 7880.84468)))
("SF_PLANTING" 0 ((13257.91855 320.51188) (13261.68971 354.44853)))
("SF_PLANTING" 0 ((13329.56301 4023.37817) (13303.16742 4032.11120) (13265.46652 4054.60034) (13259.27048 4061.09219)
(13261.68971 4072.39819)))
("SF_PLANTING" 0 ((13284.31414 3947.96380) (13261.68971 3959.27602)))
("SF_PLANTING" 0 ((13261.68971 3959.27602) (13253.99265 3977.07975) (13221.56946 4000.75373) (13227.75995 4010.86210)
(13254.14740 4013.73812) (13299.39627 3994.26934) (13329.56301 3993.21267)))
("SF_PLANTING" 0 ((13284.31414 373.30317) (13276.62398 358.37443) (13261.68971 354.44853)))
("SF_SOLAR" 0 ((13299.39627 7892.15690) (13280.39525 7862.13903) (13265.45962 7850.67873)))
("SF_PLANTING" 0 ((13265.45962 6975.86753) (13288.08405 6980.82919) (13303.16742 6990.95023)))
("SF_PLANTING" 0 ((13363.49966 965.30826) (13344.64514 972.70294) (13325.79186 972.70294) (13306.93857 967.88224)
(13280.54299 947.65984) (13269.23077 946.45645)))
("SF_SOLAR" 0 ((13273.00192 8182.50385) (13273.00192 8174.96222)))
("SF_SOLAR" 0 ((13273.00192 8133.48416) (13273.00192 8118.40113)))
("SF_SOLAR" 0 ((13273.00192 8084.46448) (13273.00192 8069.38167)))
("SF_SOLAR" 0 ((13273.00192 8024.13281) (13273.00192 8031.67421)))
("SF_SOLAR" 0 ((13273.00192 7960.03020) (13273.00192 7952.48869)))
("SF_SOLAR" 0 ((13273.00192 7926.09355) (13273.00192 7914.78133)))
("SF_MASONRY_AND_ARCH" 0 ((13273.00192 1380.09050) (13274.20611 1414.02025) (13288.08405 1421.56957)))
("SF_PLANTING" 0 ((13276.77183 6855.20362) (13276.77183 6866.51584)))
("SF_PLANTING" 0 ((13295.62636 6881.59853) (13276.77183 6866.51584)))
("SF_PLANTING" 0 ((13276.77183 6855.20362) (13291.85520 6841.32523) (13322.02070 6840.12093)))
("SF_PLANTING" 0 ((13276.77183 4083.71041) (13314.47964 4069.67749) (13329.56301 4068.62704)))
("SF_PLANTING" 0 ((13276.77183 399.69740) (13276.77183 422.32183)))
("SF_PLANTING" 0 ((13284.31414 373.30317) (13276.77183 399.69740)))
("SF_MASONRY_AND_ARCH" 0 ((13288.08405 2541.47839) (13280.54299 2586.72726)))
("SF_PLANTING" 0 ((13291.85520 6900.45249) (13284.31414 6900.45249)))
("SF_PLANTING" 0 ((13284.31414 3947.96380) (13284.46199 3925.34559) (13288.08405 3917.79830)))
("SF_PLANTING" 0 ((13333.33292 3963.04717) (13318.25079 3952.93880) (13284.31414 3947.96380)))
("SF_PLANTING" 0 ((13288.08405 3729.26052) (13284.31414 3736.80283)))
("SF_MASONRY_AND_ARCH" 0 ((13288.08405 2624.43439) (13284.31414 2613.12217)))
("SF_PLANTING" 0 ((13284.31414 1089.74265) (13288.23869 1100.90158) (13299.39627 1104.81991) (13325.79186 1101.06867)
(13359.72851 1104.67907) (13389.89400 1093.51527)))
("SF_PLANTING" 0 ((13284.31414 373.30317) (13306.93857 378.13009) (13329.56301 392.15781)))
("SF_PLANTING" 0 ((13288.08405 3917.79830) (13344.64514 3912.97048) (13355.80260 3906.34423) (13359.72851 3898.94378)))
("SF_PLANTING" 0 ((13288.08405 3910.25600) (13288.08405 3917.79830)))
("SF_PLANTING" 0 ((13288.08405 3910.25600) (13299.24842 3865.00713) (13295.62636 3842.38269)))
("SF_MASONRY_AND_ARCH" 0 ((13288.08405 2624.43439) (13284.32104 2639.51708) (13288.08405 2658.37104)))
("SF_MASONRY_AND_ARCH" 0 ((13288.08405 2624.43439) (13627.45057 2620.66369) (13642.53394 2620.66369) (13657.61731
2620.66369) (13684.01165 2620.66369)))
("SF_MASONRY_AND_ARCH" 0 ((13288.08405 2541.47839) (13329.56301 2537.55249) (13340.87523 2530.16618)))
("SF_PLANTING" 0 ((13291.85520 6900.45249) (13295.62636 6881.59853)))
("SF_PLANTING" 0 ((13291.85520 6900.45249) (13295.62636 6915.53518)))
("SF_PLANTING" 0 ((13291.85520 3834.84163) (13291.85520 3808.44604)))
("SF_PLANTING" 0 ((13291.85520 3834.84163) (13295.62636 3842.38269)))
("SF_PLANTING" 0 ((13291.85520 3808.44604) (13303.16742 3798.33857) (13337.10407 3789.59276)))
("SF_SOLAR" 0 ((13295.62636 8069.38167) (13295.62636 8080.69389) (13299.39627 8084.46448)))
("SF_SOLAR" 0 ((13295.62636 8035.44502) (13295.62636 8020.36199)))
("SF_SOLAR" 0 ((13295.62636 7982.65452) (13295.62636 7993.96674)))
("SF_SOLAR" 0 ((13299.39627 7963.80090) (13295.62636 7952.48869)))
("SF_PLANTING" 0 ((13295.62636 6881.59853) (13310.70158 6876.63032) (13317.05226 6870.27975) (13322.02070 6840.12093)))
("SF_PLANTING" 0 ((13352.18744 3842.38269) (13295.62636 3842.38269)))
("SF_PLANTING" 0 ((13310.70848 899.32127) (13309.50430 920.05452) (13303.16742 926.24853) (13295.62636 923.83201)))
("SF_PLANTING" 0 ((13310.70848 899.32127) (13295.62636 901.20758)))
("SF_SOLAR" 0 ((13559.57726 7839.36652) (13299.39627 7839.36652)))
("SF_PLANTING" 0 ((13299.39627 3239.06459) (13337.10407 3239.06459)))
("SF_MASONRY_AND_ARCH" 0 ((13299.39627 3239.06459) (13299.38937 2997.73756) (13295.63326 2978.88360) (13299.39627
2960.03043)))
("SF_MASONRY_AND_ARCH" 0 ((13299.39627 2960.03043) (13333.33292 2960.03043)))
("SF_MASONRY_AND_ARCH" 0 ((13303.16742 2911.01029) (13329.56301 2907.23982) (15874.81335 2907.23982) (15889.89253
2907.23982)))
("SF_MASONRY_AND_ARCH" 0 ((13306.93857 1429.10916) (13314.47964 1440.42138)))
("SF_PLANTING" 0 ((13306.93857 260.18100) (13306.93857 237.55656)))
("SF_PLANTING" 0 ((13378.58179 241.32636) (13363.49966 237.70430) (13306.93857 237.55656)))
("SF_SOLAR" 0 ((13314.47964 8129.71335) (13310.70848 8114.63054)))
("SF_SOLAR" 0 ((13310.70848 7918.55204) (13319.30724 7937.40577) (13358.67907 7990.19615) (13367.26957 8009.04977)))
("SF_MASONRY_AND_ARCH" 0 ((13318.25079 2032.42862) (13307.09333 2043.74706) (13310.70848 2111.61414)))
("SF_MASONRY_AND_ARCH" 0 ((13397.43631 2115.38462) (13322.02070 2115.23688) (13310.70848 2111.61414)))
("SF_PLANTING" 0 ((13344.64514 855.95871) (13322.02760 860.93337) (13315.53597 867.27579) (13310.85622 878.58314)
(13310.70848 899.32127)))
("SF_PLANTING" 0 ((13378.58179 904.97738) (13367.26957 901.35464) (13310.70848 899.32127)))
("SF_MASONRY_AND_ARCH" 0 ((13314.47964 1447.96380) (13314.47964 1440.42138)))
("SF_MASONRY_AND_ARCH" 0 ((13314.47964 1447.96380) (13318.25079 1474.35803)))
("SF_MASONRY_AND_ARCH" 0 ((13314.47964 1440.42138) (13352.18744 1436.66403) (13386.12410 1440.27432) (13397.43631
1436.65158)))
("SF_PLANTING" 0 ((13314.47964 448.71889) (13308.00057 426.09446) (13328.35894 403.47002) (13329.56301 392.15781)))
("SF_PLANTING" 0 ((13314.47964 448.71889) (13333.33292 460.03111)))
("SF_SOLAR" 0 ((13322.02070 7993.96674) (13318.25079 7978.88394)))
("SF_PLANTING" 0 ((13371.04072 6840.12093) (13322.02070 6840.12093)))
("SF_ARCHITECTURE" 0 ((13329.56301 5656.10860) (13322.16844 5678.73303) (13322.02070 5701.35747)))
("SF_ARCHITECTURE" 0 ((13322.02070 5701.35747) (13329.56991 5704.98020) (13386.12410 5705.28303) (13401.20622
5716.44050)))
("SF_PLANTING" 0 ((13322.02070 1059.57862) (13329.56301 1059.57862)))
("SF_PLANTING" 0 ((13340.87523 6949.47183) (13329.56301 6949.47183) (13325.79186 6945.70136)))
("SF_PLANTING" 0 ((13325.79186 4151.58371) (13329.56301 4068.62704)))
("SF_PLANTING" 0 ((13325.79186 4151.58371) (13306.93857 4156.54559) (13288.23314 4170.44389) (13277.96346 4185.52036)
(13273.15667 4208.13167) (13276.92647 4213.42568) (13314.47964 4197.88925) (13329.56301 4196.83258)))
("SF_PLANTING" 0 ((13325.79186 4151.58371) (13333.33292 4170.43699)))
("SF_PLANTING" 0 ((13325.79186 3755.65611) (13337.10407 3789.59276)))
("SF_PLANTING" 0 ((13325.79186 550.52885) (13343.58869 520.36199) (13353.38473 475.26154) (13367.26957 467.57070)))
("SF_PLANTING" 0 ((13371.04072 6840.12093) (13374.80498 6862.74536) (13369.84355 6881.59853) (13344.64514 6904.06889)
(13329.56301 6911.76471)))
("SF_ARCHITECTURE" 0 ((13329.56301 5656.10860) (13315.53597 5644.64830) (13311.00532 5633.48416) (13315.67681
5618.40113) (13329.56301 5599.54751)))
("SF_ARCHITECTURE" 0 ((13329.56301 5656.10860) (13495.47511 5659.87930) (13518.09955 5659.87930) (13951.73495
5659.87930) (13974.35939 5659.87930) (14019.60826 5659.87930) (14034.69038 5659.87930) (14113.87590 5659.87930)
(14132.73043 5659.87930) (14151.58371 5659.87930) (15761.69118 5659.87930) (15822.01923 5659.87930) (15840.87670
5659.87941)))
("SF_ARCHITECTURE" 0 ((13567.11957 5599.54751) (13329.56301 5599.54751)))
("SF_ARCHITECTURE" 0 ((13329.56301 5531.67421) (13299.55090 5540.27195) (13295.62636 5554.29864) (13296.83054
5576.77500) (13318.24389 5585.66889) (13329.56301 5599.54751)))
("SF_ARCHITECTURE" 0 ((13329.56301 5531.67421) (13329.56301 4196.83258)))
("SF_ARCHITECTURE" 0 ((13401.20622 5527.90305) (13382.35294 5535.29695) (13337.11097 5535.29695) (13329.56301
5531.67421)))
("SF_PLANTING" 0 ((13333.33292 4170.43699) (13329.56301 4196.83258)))
("SF_PLANTING" 0 ((13333.33292 4061.08597) (13329.56301 4068.62704)))
("SF_PLANTING" 0 ((13329.56301 4023.37817) (13329.56301 3993.21267)))
("SF_PLANTING" 0 ((13329.56301 4023.37817) (13329.71086 4053.53801) (13333.33292 4061.08597)))
("SF_PLANTING" 0 ((13333.33292 3963.04717) (13329.56301 3993.21267)))
("SF_MASONRY_AND_ARCH" 0 ((15859.72851 2869.53269) (15833.33145 2861.99095) (15674.96041 2861.99717) (15652.33597
2865.76143) (15584.46267 2865.61369) (15565.61086 2861.99095) (15493.96493 2862.13869) (15475.11312 2865.76143)
(15365.76357 2865.75520) (15346.90611 2861.99717) (15237.55656 2861.99717) (15214.93213 2865.76143) (15173.45588
2865.61369) (15158.37104 2861.99717) (14524.88688 2861.99717) (14502.26244 2865.76143) (13521.87070 2865.75520)
(13503.01618 2861.99717) (13352.18744 2861.99785) (13329.56301 2869.53269)))
("SF_MASONRY_AND_ARCH" 0 ((13329.56301 1338.61143) (13352.18744 1342.37025) (13397.43631 1338.61143)))
("SF_PLANTING" 0 ((13329.56301 1217.94966) (13352.18744 1221.71946)))
("SF_PLANTING" 0 ((13401.20622 995.47511) (13378.58179 1016.90158) (13348.41629 1025.79525) (13334.38925 1040.72398)
(13329.56301 1059.57862)))
("SF_PLANTING" 0 ((13329.56301 1059.57862) (13333.48756 1066.06946) (13344.64514 1070.74242) (13393.51742 1069.68597)
(13418.85667 1040.72398) (13419.91301 1014.32975) (13416.28959 999.24491)))
("SF_PLANTING" 0 ((13340.87523 603.31731) (13329.56301 595.77771)))
("SF_PLANTING" 0 ((13329.56301 392.15781) (13363.49276 392.30486) (13371.04072 395.92760)))
("SF_PLANTING" 0 ((13352.18744 301.66007) (13329.56301 275.26301)))
("SF_PLANTING" 0 ((13401.20622 4147.81256) (13378.58179 4148.86301) (13333.33292 4170.43699)))
("SF_PLANTING" 0 ((13333.33292 4061.08597) (13374.81188 4053.54491)))
("SF_PLANTING" 0 ((13333.33292 3963.04717) (13371.04072 3948.11188) (13386.12410 3948.11844) (13401.20622 3955.50486)))
("SF_MASONRY_AND_ARCH" 0 ((13382.35294 2960.03043) (13359.72851 2956.25916) (13333.33292 2960.03043)))
("SF_MASONRY_AND_ARCH" 0 ((13337.10407 3239.06459) (13333.33982 3223.98190) (13333.33292 2960.03043)))
("SF_SOLAR" 0 ((13340.87523 8069.38167) (13340.87523 8080.69389) (13337.10407 8084.46448)))
("SF_SOLAR" 0 ((13337.10407 7869.53247) (13529.41176 7869.53247)))
("SF_PLANTING" 0 ((13371.04072 3800.90498) (13337.10407 3789.59276)))
("SF_PLANTING" 0 ((13382.35294 3235.29412) (13367.26957 3242.68733) (13337.10407 3239.06459)))
("SF_SOLAR" 0 ((13344.64514 8118.40113) (13340.87523 8125.94276)))
("SF_MASONRY_AND_ARCH" 0 ((13340.87523 1636.50170) (13340.87523 1602.56505)))
("SF_MASONRY_AND_ARCH" 0 ((13348.41629 1598.79242) (13340.87523 1602.56505)))
("SF_PLANTING" 0 ((13340.87523 935.14423) (13359.72851 938.91403)))
("SF_PLANTING" 0 ((13367.26957 595.77771) (13340.87523 603.31731)))
("SF_PLANTING" 0 ((13344.64514 855.95871) (13344.63824 742.83654) (13341.17081 727.75170) (13344.49729 716.43948)
(13344.63824 637.25396) (13340.87523 603.31731)))
("SF_SOLAR" 0 ((13344.64514 8039.21561) (13348.41629 8035.44502) (13348.41629 8024.13281)))
("SF_SOLAR" 0 ((13348.41629 7941.17647) (13344.64514 7952.48869)))
("SF_PLANTING" 0 ((13344.64514 855.95871) (13359.72851 859.72851) (13442.68518 859.72229) (13465.30962 855.95871)
(13536.95283 856.10577) (13555.80735 859.72851) (13687.78281 855.95781) (13710.40724 855.95781) (13831.07048 855.95781)
(13853.69491 855.95781) (13891.40271 855.95781) (13989.44152 855.95781) (14012.06595 855.95781) (14106.33484 855.95781)
(14125.18812 855.95781) (15742.83371 855.95781) (15761.69118 855.95781) (15784.31561 855.95781)))
("SF_PLANTING" 0 ((13344.64514 324.28450) (13363.49966 331.82410)))
("SF_PLANTING" 0 ((13344.64559 6048.26538) (13344.64559 6070.88982) (13344.64559 6365.00747) (13344.64559 6387.63190)
(13344.64559 6402.71493) (13344.64559 6478.12964)))
("SF_PLANTING" 0 ((13382.35294 6561.08597) (13381.14876 6485.67783) (13371.04072 6478.28428) (13344.64559 6478.12964)))
("SF_ARCHITECTURE" 0 ((13344.64559 6048.26538) (13412.51844 6048.41346) (13427.60181 6052.02964) (15414.77941
6052.02964) (15433.63688 6048.27195) (15708.89706 6048.25882) (15750.37896 6040.72398)))
("SF_SOLAR" 0 ((13367.26957 7941.17647) (13348.41629 7922.32274)))
("SF_MASONRY_AND_ARCH" 0 ((13348.41629 1598.79242) (13343.58869 1583.85814) (13319.44808 1564.85090) (13315.68382
1542.23891) (13325.79186 1534.84502) (13393.66516 1534.69174)))
("SF_MASONRY_AND_ARCH" 0 ((13348.41629 1598.79242) (13386.12410 1598.94084) (13397.43631 1602.56505)))
("SF_PLANTING" 0 ((13352.18744 3842.38269) (13371.04072 3800.90498)))
("SF_PLANTING" 0 ((13352.18744 3842.38269) (13363.49966 3857.46606)))
("SF_PLANTING" 0 ((13438.91403 3865.00713) (13431.22387 3879.04072) (13401.20622 3897.74649) (13359.72851 3898.94378)))
("SF_PLANTING" 0 ((13363.49966 3857.46606) (13359.87624 3865.01403) (13359.72851 3898.94378)))
("SF_PLANTING" 0 ((13359.72851 938.91403) (13378.58179 935.14423)))
("SF_PLANTING" 0 ((13359.72851 938.91403) (13363.49966 965.30826)))
("SF_SOLAR" 0 ((13363.49966 8122.17195) (13363.49966 8133.48416)))
("SF_PLANTING" 0 ((13374.81188 3857.46606) (13363.49966 3857.46606)))
("SF_MASONRY_AND_ARCH" 0 ((13389.89400 2530.16618) (13371.04762 2540.28043) (13363.49966 2537.70713)))
("SF_PLANTING" 0 ((13363.49966 965.30826) (13389.89400 969.08088)))
("SF_SOLAR" 0 ((13506.78733 8163.65000) (13480.39174 8166.21652) (13470.12896 8159.73122) (13396.37998 8046.75724)
(13367.26957 8009.04977)))
("SF_SOLAR" 0 ((13371.04072 7971.34231) (13367.26957 7982.65452)))
("SF_SOLAR" 0 ((13634.99287 8005.27896) (13597.13733 7948.71799) (13582.20170 7937.56041) (13555.80735 7941.16991)
(13536.95283 7937.55385) (13484.16290 7937.40577) (13461.53846 7941.16991) (13367.26957 7941.17647)))
("SF_SOLAR" 0 ((13506.78733 8163.65000) (13501.96663 8148.56719) (13473.90701 8110.85973) (13437.85769 8050.52783)
(13375.86833 7963.80090) (13367.26957 7941.17647)))
("SF_PLANTING" 0 ((13548.26505 561.84016) (13382.35294 565.76550) (13372.24491 573.15814) (13367.26957 595.77771)))
("SF_PLANTING" 0 ((13367.26957 595.77771) (13386.12410 599.54751) (15761.69118 599.54751) (15776.77036 595.77771)))
("SF_PLANTING" 0 ((13371.04072 395.92760) (13367.26957 467.57070)))
("SF_PLANTING" 0 ((13382.35294 475.11312) (13367.26957 467.57070)))
("SF_PLANTING" 0 ((13371.04072 6840.12093) (13389.89400 6836.34966)))
("SF_PLANTING" 0 ((13371.04072 3800.90498) (13408.74853 3808.44604)))
("SF_PLANTING" 0 ((13382.35294 395.92760) (13371.04072 395.92760)))
("SF_PLANTING" 0 ((13393.66516 4061.08597) (13384.92692 4091.25147) (13374.81188 4102.56369)))
("SF_PLANTING" 0 ((13401.20622 4004.52489) (13385.22240 4019.61448) (13374.81188 4053.54491)))
("SF_PLANTING" 0 ((13393.66516 4061.08597) (13374.81188 4053.54491)))
("SF_PLANTING" 0 ((13374.81188 3996.98382) (13378.73643 3990.63314) (13395.55011 3985.67161)))
("SF_PLANTING" 0 ((13374.81188 3857.46606) (13390.04310 3831.07048) (13408.74853 3815.98835)))
("SF_PLANTING" 0 ((13374.81188 3857.46606) (13389.89400 3868.77828)))
("SF_PLANTING" 0 ((13374.81188 3725.49061) (13404.97738 3732.88360) (13453.99740 3732.88360) (13465.30962 3729.26052)))
("SF_SOLAR" 0 ((13382.35294 7993.96674) (13378.58179 8005.27896)))
("SF_PLANTING" 0 ((13378.58179 935.14423) (13378.58179 904.97738)))
("SF_PLANTING" 0 ((13378.58179 935.14423) (13388.84446 953.99604) (13389.89400 969.08088)))
("SF_PLANTING" 0 ((13423.83066 904.97738) (13378.58179 904.97738)))
("SF_PLANTING" 0 ((13378.58179 241.32636) (13389.89400 237.70430) (13442.68518 237.55656)))
("SF_PLANTING" 0 ((13404.97738 279.03563) (13387.18054 263.80373) (13378.58179 241.32636)))
("SF_ARCHITECTURE" 0 ((13382.35294 6561.08597) (15569.38348 6561.08597) (15603.31821 6564.85645)))
("SF_PLANTING" 0 ((13382.35294 6561.08597) (13382.50758 6715.68654) (13393.66516 6729.71324) (13422.77421 6746.00023)
(13430.32353 6764.70588) (13431.37296 6779.78857)))
("SF_MASONRY_AND_ARCH" 0 ((13382.35294 3235.29412) (13382.34604 3009.04977) (13378.58179 2986.42534) (13382.35294
2960.03043)))
("SF_PLANTING" 0 ((13420.06075 3239.06459) (13389.90090 3238.91686) (13382.35294 3235.29412)))
("SF_MASONRY_AND_ARCH" 0 ((13382.35294 2960.03043) (13420.06075 2960.03043)))
("SF_PLANTING" 0 ((13382.35294 395.92760) (13391.09808 346.90894) (13404.97738 335.59672)))
("SF_PLANTING" 0 ((13382.35294 395.92760) (13408.59943 407.38824) (13469.22862 490.19514) (13487.93405 508.90204)
(13506.78733 520.36199)))
("SF_SOLAR" 0 ((13386.12410 7918.55204) (13389.89400 7929.86425)))
("SF_MASONRY_AND_ARCH" 0 ((13389.89400 2530.16618) (13386.27195 2522.61753) (13386.12410 2466.06335)))
("SF_MASONRY_AND_ARCH" 0 ((13386.12410 2292.60962) (13389.89400 2202.11188)))
("SF_PLANTING" 0 ((13389.89400 6836.34966) (13397.44321 6826.23518) (13408.74853 6822.31640) (13453.99740 6821.11867)
(13469.07952 6813.72523)))
("SF_PLANTING" 0 ((13389.89400 6836.34966) (13431.37296 6851.28484) (13506.78733 6851.27828) (13517.94491 6840.12059)
(13514.32839 6821.26697)))
("SF_MASONRY_AND_ARCH" 0 ((13389.89400 2530.16618) (13412.51844 2533.93665) (13465.30962 2533.78891) (13476.62183
2530.46233) (13487.93405 2533.78891) (13563.34842 2533.93043) (13585.97285 2530.16618) (13623.68066 2533.93043)
(13638.76278 2530.31391) (13691.55396 2530.16618)))
("SF_MASONRY_AND_ARCH" 0 ((13404.97738 2198.34061) (13389.89400 2202.11188)))
("SF_PLANTING" 0 ((13401.20622 995.47511) (13389.89400 969.08088)))
("SF_PLANTING" 0 ((13393.66516 4061.08597) (13416.28959 4053.54491)))
("SF_PLANTING" 0 ((13403.09242 3964.93213) (13395.55011 3985.67161)))
("SF_PLANTING" 0 ((13401.20622 3993.21267) (13393.66516 3989.44152) (13395.55011 3985.67161)))
("SF_PLANTING" 0 ((13401.20622 3993.21267) (13395.55011 3985.67161)))
("SF_SOLAR" 0 ((13397.43631 7975.11312) (13423.83066 7977.68620) (13453.99740 7971.34887) (13601.05622 7971.34231)))
("SF_SOLAR" 0 ((13401.20622 8035.44502) (13404.97738 8027.90339)))
("SF_ARCHITECTURE" 0 ((13431.37296 5716.44050) (13401.20622 5716.44050)))
("SF_ARCHITECTURE" 0 ((13401.20622 4147.81256) (13401.05837 4215.68586) (13397.43631 4234.54038) (13401.19932
4283.55916) (13401.20622 5527.90305)))
("SF_ARCHITECTURE" 0 ((13476.62183 5527.90305) (13453.99740 5535.44536) (13416.28959 5535.29038) (13401.20622
5527.90305)))
("SF_PLANTING" 0 ((13401.20622 4147.81256) (13424.88009 4095.02262) (13442.68518 4072.39819)))
("SF_PLANTING" 0 ((13401.20622 4004.52489) (13401.20622 3993.21267)))
("SF_PLANTING" 0 ((13401.20622 4004.52489) (13416.28959 4007.23937) (13461.53846 3989.44152)))
("SF_PLANTING" 0 ((13504.90238 3915.91210) (13487.93405 3906.64005) (13461.53846 3911.44762) (13420.06629 3934.07828)
(13401.20622 3955.50486)))
("SF_PLANTING" 0 ((13401.20622 3955.50486) (13403.09242 3964.93213)))
("SF_PLANTING" 0 ((13401.20622 995.47511) (13416.28959 999.24491)))
("SF_PLANTING" 0 ((13403.09242 3964.93213) (13408.74853 3963.04717) (13412.51844 3970.58824)))
("SF_PLANTING" 0 ((13403.09242 3964.93213) (13412.51844 3970.58824)))
("SF_SOLAR" 0 ((13404.97738 8118.40113) (13412.51844 8129.71335)))
("SF_PLANTING" 0 ((13404.97738 1168.92817) (13389.90090 1172.53846) (13383.55713 1168.77489) (13383.40928 1153.84615)
(13390.95034 1138.76414) (13427.74955 1094.71867) (13457.76731 1089.74265)))
("SF_PLANTING" 0 ((13404.97738 279.03563) (13401.50170 320.51188) (13404.97738 335.59672)))
("SF_PLANTING" 0 ((13469.07952 328.05430) (13453.99740 334.53959) (13423.83066 339.21810) (13404.97738 335.59672)))
("SF_PLANTING" 0 ((13442.68518 271.49321) (13404.97738 279.03563)))
("SF_PLANTING" 0 ((13408.74853 3815.98835) (13408.74853 3808.44604)))
("SF_PLANTING" 0 ((13438.91403 3865.00713) (13437.70984 3838.61900) (13408.74853 3815.98835)))
("SF_PLANTING" 0 ((13457.76731 3800.90498) (13420.06075 3801.05962) (13408.74853 3808.44604)))
("SF_SOLAR" 0 ((13412.51844 7963.80090) (13412.51844 7956.25939)))
("SF_PLANTING" 0 ((13416.28959 4053.54491) (13412.51844 4038.46154)))
("SF_PLANTING" 0 ((13461.53846 3978.12930) (13435.14287 3968.01493) (13412.51844 3970.58824)))
("SF_SOLAR" 0 ((13431.37296 8058.06946) (13427.60181 8061.84005) (13416.28959 8061.84005)))
("SF_PLANTING" 0 ((13416.28959 4053.54491) (13442.68518 4057.31482)))
("SF_PLANTING" 0 ((13446.45509 999.24491) (13431.37296 995.47511) (13416.28959 999.24491)))
("SF_PLANTING" 0 ((13420.06075 3239.06459) (13446.44819 3238.91686) (13453.99740 3235.29412)))
("SF_MASONRY_AND_ARCH" 0 ((13420.06075 3239.06459) (13420.06075 2960.03043)))
("SF_MASONRY_AND_ARCH" 0 ((13420.06075 2960.03043) (13435.14287 2956.25916) (13453.99740 2960.03043)))
("SF_ARCHITECTURE" 0 ((13423.83066 6436.65158) (13442.68518 6444.19310) (15546.75905 6440.42896) (15569.38348
6444.19299) (15644.79638 6444.04480) (15656.10860 6440.57059) (15754.14593 6436.65158)))
("SF_PLANTING" 0 ((13480.39174 912.51980) (13461.53846 897.59027) (13435.14287 897.59027) (13423.83066 904.97738)))
("SF_PLANTING" 0 ((13480.39174 912.51980) (13469.07952 926.39695) (13446.45509 927.45407) (13431.52771 922.63337)
(13423.83066 904.97738)))
("SF_SOLAR" 0 ((13529.41176 8016.59118) (13427.60181 8012.82059)))
("SF_PLANTING" 0 ((13457.76731 1150.07636) (13438.91403 1151.27975) (13427.60181 1161.38857)))
("SF_SOLAR" 0 ((13431.37296 8084.46448) (13438.91403 8073.15226)))
("SF_PLANTING" 0 ((13469.07952 6813.72523) (13468.92477 6791.10735) (13465.15498 6784.61584) (13453.99740 6779.93688)
(13431.37296 6779.78857)))
("SF_ARCHITECTURE" 0 ((13431.37296 6489.44186) (15154.59989 6489.44842) (15177.22285 6493.21267) (15279.03281
6493.20611) (15301.65724 6489.44186) (15697.58484 6493.20611) (15723.98190 6489.44186)))
("SF_ARCHITECTURE" 0 ((13729.26052 5720.21109) (13717.94830 5710.10294) (13680.24174 5701.35747) (13446.45509
5705.28303) (13431.37296 5716.44050)))
("SF_ARCHITECTURE" 0 ((13729.26052 5720.21109) (13721.71256 5731.36855) (13714.17839 5735.13948) (13487.93405
5735.28756) (13446.45509 5730.31912) (13431.37296 5716.44050)))
("SF_PLANTING" 0 ((13438.91403 972.85068) (13431.37296 961.53846)))
("SF_PLANTING" 0 ((13476.62183 328.05430) (13475.42330 346.90894) (13464.11109 369.53337) (13446.45509 388.23190)
(13435.14287 392.15781)))
("SF_PLANTING" 0 ((13438.91403 3865.00713) (13453.99740 3863.95102) (13480.39174 3846.15385)))
("SF_PLANTING" 0 ((13442.68518 4057.31482) (13442.68518 4072.39819)))
("SF_PLANTING" 0 ((13476.62183 4257.16482) (13461.68620 4245.85192) (13454.14525 4230.76923) (13454.14525 4193.06143)
(13461.39072 4162.89593) (13461.39072 4128.95928) (13452.79333 4083.71041) (13442.68518 4072.39819)))
("SF_PLANTING" 0 ((13461.53846 3989.44152) (13465.15498 4004.52489) (13456.57002 4042.23269) (13442.68518 4057.31482)))
("SF_PLANTING" 0 ((13442.68518 271.49321) (13476.62183 266.52477) (13491.70396 248.86878)))
("SF_PLANTING" 0 ((13442.68518 271.49321) (13442.68518 237.55656)))
("SF_PLANTING" 0 ((13442.68518 271.49321) (13447.65226 294.11765) (13469.07952 328.05430)))
("SF_PLANTING" 0 ((13491.70396 248.86878) (13476.62183 237.71120) (13442.68518 237.55656)))
("SF_SOLAR" 0 ((13446.45509 8107.08891) (13450.22624 8099.54751) (13453.99740 8099.54751)))
("SF_PLANTING" 0 ((13446.45509 999.24491) (13454.14525 988.08111) (13472.85068 973.90701) (13487.93405 969.08088)))
("SF_PLANTING" 0 ((13446.45509 999.24491) (13457.77421 1014.32217) (13469.07952 1021.71606) (13487.93405 1020.81369)
(13503.01618 1012.44344)))
("SF_SOLAR" 0 ((13450.22624 8182.50385) (13450.22624 8174.96222)))
("SF_MASONRY_AND_ARCH" 0 ((13457.76731 2405.73179) (13450.22624 2405.73179)))
("SF_SOLAR" 0 ((13691.55396 8099.54751) (13675.42115 8069.38167) (13661.38722 8058.22410) (13453.99740 8058.06946)))
("SF_SOLAR" 0 ((13453.99740 7963.80090) (13453.99740 7952.48869)))
("SF_MASONRY_AND_ARCH" 0 ((13453.99740 3235.29412) (13453.99740 2960.03043)))
("SF_PLANTING" 0 ((13503.01618 3235.29412) (13480.39174 3242.82896) (13453.99740 3235.29412)))
("SF_MASONRY_AND_ARCH" 0 ((13503.01618 2960.03043) (13484.16290 2956.25916) (13453.99740 2960.03043)))
("SF_SOLAR" 0 ((13457.76731 8024.13281) (13457.76731 8031.67421)))
("SF_PLANTING" 0 ((13563.34842 3808.44604) (13533.18292 3793.65984) (13518.09955 3797.12760) (13472.85068 3794.56120)
(13457.76731 3800.90498)))
("SF_PLANTING" 0 ((13457.76731 3800.90498) (13480.39174 3846.15385)))
("SF_PLANTING" 0 ((13457.76731 1150.07636) (13476.62183 1146.30373)))
("SF_PLANTING" 0 ((13457.76731 1150.07636) (13457.76731 1089.74265)))
("SF_MASONRY_AND_ARCH" 0 ((13457.76731 1150.07636) (13457.92195 2209.65283) (13461.69310 2217.04615) (13476.62183
2224.58778) (13570.88948 2224.73631)))
("SF_PLANTING" 0 ((13503.01618 1012.44344) (13498.04219 1055.80600) (13484.16290 1069.83371) (13465.31652 1078.58575)
(13457.76731 1089.74265)))
("SF_PLANTING" 0 ((13461.53846 3978.12930) (13461.53846 3989.44152)))
("SF_PLANTING" 0 ((13504.90238 3915.91210) (13485.21923 3936.65158) (13461.53846 3978.12930)))
("SF_SOLAR" 0 ((13465.30962 8137.25498) (13472.85068 8125.94276)))
("SF_PLANTING" 0 ((13510.55848 328.05430) (13520.81437 346.90894) (13520.81437 361.99095) (13502.86143 395.92760)
(13480.39174 417.50260) (13469.23416 423.84638) (13465.30962 422.32183)))
("SF_PLANTING" 0 ((13469.07952 6813.72523) (13476.62873 6819.92127) (13495.47511 6817.49649)))
("SF_PLANTING" 0 ((13476.62183 328.05430) (13469.07952 328.05430)))
("SF_SOLAR" 0 ((13476.62183 7982.65452) (13480.39174 7993.96674)))
("SF_ARCHITECTURE" 0 ((13476.62183 5527.90305) (13476.61493 4570.13575) (13472.85068 4547.51131) (13476.62183
4483.40916) (13472.85758 4453.24242) (13472.85758 4306.18360) (13476.62183 4257.16482)))
("SF_ARCHITECTURE" 0 ((13476.62183 5527.90305) (13487.93405 5534.24751) (13514.32839 5539.21527) (13529.41176
5538.16572) (13552.03620 5527.90305)))
("SF_PLANTING" 0 ((13525.64061 4147.81256) (13510.70633 4155.50271) (13504.06561 4166.66708) (13491.85170 4208.14480)
(13486.87771 4242.08145) (13476.62183 4257.16482)))
("SF_PLANTING" 0 ((13476.62183 328.05430) (13510.55848 328.05430)))
("SF_SOLAR" 0 ((13691.55396 8099.54751) (13684.00475 8103.16369) (13631.22172 8099.55407) (13604.82613 8103.31833)
(13503.01618 8103.31176) (13480.39174 8099.54751)))
("SF_SOLAR" 0 ((13480.39174 7918.55204) (13484.16290 7926.09355)))
("SF_PLANTING" 0 ((13510.55848 3868.77828) (13495.47511 3853.84989) (13480.39174 3846.15385)))
("SF_PLANTING" 0 ((13480.39174 912.51980) (13506.78043 912.66686) (13514.32839 916.28959)))
("SF_SOLAR" 0 ((13484.16290 8001.50837) (13495.47511 7994.12138) (13529.41176 7994.11493) (13563.34842 8012.66584)
(13634.99287 8012.96855) (13646.30509 8016.59118)))
("SF_SOLAR" 0 ((13495.47511 8080.69389) (13487.93405 8073.15226)))
("SF_SOLAR" 0 ((13487.93405 7952.48869) (13487.93405 7960.03020)))
("SF_PLANTING" 0 ((13514.32839 916.28959) (13487.93405 969.08088)))
("SF_PLANTING" 0 ((13503.01618 1012.44344) (13494.27794 976.62805) (13487.93405 969.08088)))
("SF_PLANTING" 0 ((13491.70396 248.86878) (13499.24627 248.86878)))
("SF_SOLAR" 0 ((13499.24627 8024.13281) (13499.24627 8039.21561)))
("SF_PLANTING" 0 ((13536.95283 1085.97285) (13514.48303 1104.82749) (13499.24627 1127.45192)))
("SF_PLANTING" 0 ((13499.24627 263.95079) (13499.24627 248.86878)))
("SF_PLANTING" 0 ((13548.26505 248.86878) (13499.24627 248.86878)))
("SF_PLANTING" 0 ((13540.72398 3691.55396) (13531.98439 3657.76516) (13503.01618 3631.22172)))
("SF_MASONRY_AND_ARCH" 0 ((13503.01618 2960.03043) (13503.00928 3069.38133) (13499.24627 3092.00577) (13503.01618
3235.29412)))
("SF_PLANTING" 0 ((13503.01618 3235.29412) (13510.56538 3238.91686) (13536.95283 3239.06459)))
("SF_MASONRY_AND_ARCH" 0 ((13503.01618 2960.03043) (13536.95283 2960.03043)))
("SF_PLANTING" 0 ((13521.87025 1187.78281) (13503.01618 1187.78281)))
("SF_PLANTING" 0 ((13503.01618 1012.44344) (13544.49514 1010.55713)))
("SF_PLANTING" 0 ((13504.90238 3915.91210) (13510.40667 3902.71799) (13510.55848 3868.77828)))
("SF_PLANTING" 0 ((13504.90238 3915.91210) (13521.71606 3932.88043) (13525.64061 3944.19265)))
("SF_SOLAR" 0 ((13506.78733 8163.65000) (13770.73948 8163.65000)))
("SF_PLANTING" 0 ((13544.49514 3623.68066) (13533.18292 3613.42421) (13510.71324 3603.63575) (13506.78733 3597.28507)))
("SF_SOLAR" 0 ((13510.55848 8174.96222) (13514.32839 8182.50385)))
("SF_SOLAR" 0 ((13510.55848 8141.02557) (13601.05622 8141.03213) (13619.90950 8144.78971) (13638.76278 8141.17364)
(13710.40724 8141.02557)))
("SF_PLANTING" 0 ((13540.72398 3868.77828) (13510.55848 3868.77828)))
("SF_MASONRY_AND_ARCH" 0 ((13521.87070 2488.68778) (13522.62466 2477.37557) (13511.76267 2450.98066) (13521.71606
2413.27274) (13510.55848 2401.96052)))
("SF_PLANTING" 0 ((13510.55848 328.05430) (13521.87624 314.16946) (13540.72398 308.15090) (13555.80735 297.88744)))
("SF_PLANTING" 0 ((13514.32839 3751.88495) (13525.64061 3761.99333) (13552.03620 3763.19717)))
("SF_MASONRY_AND_ARCH" 0 ((13514.32839 2360.48292) (13521.87070 2360.48292)))
("SF_PLANTING" 0 ((13514.32839 916.28959) (13533.18292 920.05939)))
("SF_SOLAR" 0 ((13518.09955 8197.58665) (13518.09955 8190.04525)))
("SF_PLANTING" 0 ((13540.72398 3733.03167) (13518.09955 3725.49061)))
("SF_MASONRY_AND_ARCH" 0 ((13521.87025 1187.78281) (13521.87025 1199.09502) (13521.87025 1236.80147) (13521.87025
2168.17523) (13521.87025 2183.25792)))
("SF_PLANTING" 0 ((13521.87025 1187.78281) (13523.07489 1153.85238) (13548.26505 1138.76414)))
("SF_SOLAR" 0 ((13525.64061 8133.48416) (13521.87070 8118.40113)))
("SF_SOLAR" 0 ((13521.87070 8069.38167) (13529.41176 8080.69389)))
("SF_PLANTING" 0 ((13521.87070 3548.26572) (13540.72398 3566.97115) (13563.34842 3581.00441) (13589.74400 3582.20238)))
("SF_PLANTING" 0 ((13525.64061 3944.19265) (13518.25419 3955.50554) (13514.48303 3996.98382) (13521.72296 4049.77376)
(13522.01855 4128.95928) (13525.64061 4147.81256)))
("SF_ARCHITECTURE" 0 ((13525.64061 4147.81256) (13535.75554 4159.12545) (13552.02930 4245.85260) (13552.03620
5527.90305)))
("SF_PLANTING" 0 ((13525.64061 3944.19265) (13547.06776 3959.28224) (13559.57726 3993.21267)))
("SF_SOLAR" 0 ((13544.49514 8012.82059) (13529.41176 8016.59118)))
("SF_SOLAR" 0 ((13529.41176 8016.59118) (13530.60894 8024.13937) (13548.26505 8046.75724)))
("SF_PLANTING" 0 ((13533.18292 3695.32387) (13540.72398 3691.55396)))
("SF_PLANTING" 0 ((13661.38722 912.51980) (13638.76278 897.58337) (13585.97285 897.58337) (13548.26505 902.41097)
(13533.18292 920.05939)))
("SF_PLANTING" 0 ((13540.72398 931.37161) (13533.18292 920.05939)))
("SF_MASONRY_AND_ARCH" 0 ((13536.95283 2960.03043) (13536.80498 3012.82025) (13533.18292 3031.67421) (13533.18982
3178.73303) (13536.80498 3193.81572) (13536.95283 3239.06459)))
("SF_PLANTING" 0 ((13574.66063 3239.06459) (13559.57726 3242.83586) (13536.95283 3239.06459)))
("SF_MASONRY_AND_ARCH" 0 ((13536.95283 2960.03043) (13570.88948 2960.03043)))
("SF_PLANTING" 0 ((13536.95283 1085.97285) (13536.95283 1078.43043) (13544.49514 1074.66063)))
("SF_PLANTING" 0 ((13536.95283 1085.97285) (13544.34050 1097.28507) (13548.26505 1138.76414)))
("SF_SOLAR" 0 ((13540.72398 7884.61538) (13540.72398 7892.15690)))
("SF_PLANTING" 0 ((13540.72398 3868.77828) (13553.09253 3838.61900) (13563.34842 3831.07048)))
("SF_PLANTING" 0 ((13563.34842 3876.31934) (13540.72398 3868.77828)))
("SF_PLANTING" 0 ((13548.26505 3695.32387) (13540.72398 3691.55396)))
("SF_PLANTING" 0 ((13540.72398 931.37161) (13544.49514 1010.55713)))
("SF_PLANTING" 0 ((13540.72398 931.37161) (13567.11957 931.52692) (13593.51391 945.39932) (13604.82613 946.45645)))
("SF_SOLAR" 0 ((13544.49514 8182.50385) (13544.49514 8174.96222)))
("SF_SOLAR" 0 ((13544.49514 7960.03020) (13544.49514 7952.48869)))
("SF_SOLAR" 0 ((13544.49514 7918.55204) (13548.26505 7929.86425)))
("SF_PLANTING" 0 ((13544.49514 1074.66063) (13544.49514 1010.55713)))
("SF_PLANTING" 0 ((13601.05622 1116.13971) (13574.66063 1082.35633) (13544.49514 1074.66063)))
("SF_PLANTING" 0 ((13544.49514 1010.55713) (13601.05622 1018.09955)))
("SF_SOLAR" 0 ((13555.80735 7993.96674) (13548.26505 7982.65452)))
("SF_SOLAR" 0 ((13555.80735 7869.53247) (13548.26505 7869.53247)))
("SF_PLANTING" 0 ((13548.26505 3695.32387) (13555.81425 3688.98043) (13567.11957 3687.93088) (13592.45747 3702.87240)
(13600.90158 3744.33767) (13597.13733 3750.68111) (13589.74400 3751.88495)))
("SF_PLANTING" 0 ((13548.26505 3695.32387) (13555.96210 3710.40724) (13589.74400 3751.88495)))
("SF_PLANTING" 0 ((13559.57726 1153.84615) (13548.26505 1138.76414)))
("SF_PLANTING" 0 ((13548.26505 561.84016) (14196.83258 561.84016) (14219.45701 561.84016) (14343.89140 561.84016)
(14362.74468 561.84016) (15418.55204 565.60464) (15433.63688 561.84106)))
("SF_PLANTING" 0 ((13548.26505 561.84016) (13548.41278 527.90441) (13555.80735 512.81957)))
("SF_PLANTING" 0 ((13616.13835 241.32636) (13563.34842 237.71120) (13548.26505 248.86878)))
("SF_PLANTING" 0 ((13548.26505 248.86878) (13555.80735 297.88744)))
("SF_SOLAR" 0 ((13552.03620 8118.40113) (13552.03620 8129.71335)))
("SF_ARCHITECTURE" 0 ((13627.45057 5531.67421) (13612.36844 5539.06131) (13578.43179 5539.06742) (13552.03620
5527.90305)))
("SF_PLANTING" 0 ((13567.11957 305.42986) (13553.24038 316.74208) (13552.03620 335.59672)))
("SF_PLANTING" 0 ((13589.74400 3570.89016) (13569.69910 3521.87002) (13555.80735 3499.24559)))
("SF_PLANTING" 0 ((13555.80735 3442.68450) (13563.34842 3465.30894)))
("SF_MASONRY_AND_ARCH" 0 ((13555.80735 2138.00905) (13578.43133 2138.00905)))
("SF_MASONRY_AND_ARCH" 0 ((13555.80735 2138.00905) (13552.03620 2077.67749) (13555.80690 1259.42590) (13555.80690
1221.71946) (13555.80690 1172.70079) (13559.57726 1153.84615)))
("SF_MASONRY_AND_ARCH" 0 ((13555.80735 2138.00905) (13555.96210 2175.71618) (13567.11957 2187.02839)))
("SF_PLANTING" 0 ((13555.80735 358.22115) (13564.54016 392.15781) (13574.66063 407.23982)))
("SF_PLANTING" 0 ((13567.11957 297.88744) (13555.80735 297.88744)))
("SF_SOLAR" 0 ((13559.57726 8069.38167) (13570.88948 8092.00611)))
("SF_PLANTING" 0 ((13608.59729 3993.21267) (13559.57726 3993.21267)))
("SF_PLANTING" 0 ((13567.11957 4038.46154) (13559.57726 3993.21267)))
("SF_PLANTING" 0 ((13559.57726 3472.85068) (13563.34842 3465.30894)))
("SF_PLANTING" 0 ((13585.97285 1172.70079) (13578.28269 1162.44355) (13559.57726 1153.84615)))
("SF_PLANTING" 0 ((13563.34842 3876.31934) (13616.13835 3876.16538) (13631.22172 3861.23722)))
("SF_PLANTING" 0 ((13614.25339 3955.50486) (13593.51391 3929.11674) (13568.32376 3910.25600) (13563.34842 3876.31934)))
("SF_PLANTING" 0 ((13563.34842 3808.44604) (13563.34842 3831.07048)))
("SF_PLANTING" 0 ((13627.45057 3842.38269) (13582.20170 3838.46437) (13563.34842 3831.07048)))
("SF_PLANTING" 0 ((13563.34842 3808.44604) (13570.88948 3800.90498) (13578.43179 3800.90498)))
("SF_PLANTING" 0 ((13604.82613 3495.47511) (13563.34842 3465.30894)))
("SF_ARCHITECTURE" 0 ((13733.03167 5599.54751) (13706.63609 5588.23529) (13578.43179 5588.23529) (13567.11957
5599.54751)))
("SF_ARCHITECTURE" 0 ((13733.03167 5599.54751) (13717.94830 5617.19695) (13589.74400 5618.24638) (13567.11957
5599.54751)))
("SF_PLANTING" 0 ((13627.45057 4291.10147) (13616.28744 4283.55294) (13608.75192 4268.47704) (13614.94106 4238.31029)
(13612.22070 4219.45701) (13587.02919 4155.35486) (13571.93891 4102.56369) (13563.50305 4053.54491) (13567.11957
4038.46154)))
("SF_PLANTING" 0 ((13627.45057 4046.00260) (13601.05622 4045.85475) (13567.11957 4038.46154)))
("SF_MASONRY_AND_ARCH" 0 ((13567.11957 2187.02839) (13578.43133 2175.71618) (13578.43133 2138.00905)))
("SF_MASONRY_AND_ARCH" 0 ((13567.11957 2187.02839) (13570.88948 2224.73631)))
("SF_PLANTING" 0 ((13601.05622 444.94627) (13579.62907 456.40690) (13567.11957 486.42534)))
("SF_PLANTING" 0 ((13567.11957 305.42986) (13567.11957 297.88744)))
("SF_PLANTING" 0 ((13567.11957 305.42986) (13589.74400 324.28450)))
("SF_PLANTING" 0 ((13567.11957 297.88744) (13582.20170 286.73054) (13616.13835 290.19253) (13646.30509 279.03563)))
("SF_SOLAR" 0 ((13582.20170 8042.98643) (13570.88948 8024.13281)))
("SF_SOLAR" 0 ((13570.88948 7850.67873) (13567.26742 7869.53247) (13578.43179 7892.15690)))
("SF_SOLAR" 0 ((13706.63609 7839.36652) (13684.01165 7839.36652) (13676.47059 7843.13722) (13650.06946 7839.36652)
(13570.88948 7839.36652)))
("SF_MASONRY_AND_ARCH" 0 ((13570.88948 2960.03043) (13604.82613 2960.03043)))
("SF_MASONRY_AND_ARCH" 0 ((13574.66063 3239.06459) (13574.51290 3163.65034) (13570.88948 3144.79638) (13570.89638
3009.04977) (13574.65373 2978.88360) (13570.88948 2960.03043)))
("SF_MASONRY_AND_ARCH" 0 ((15663.64819 1168.92817) (15667.41391 1180.24038) (15667.42081 2209.65283) (15652.33597
2223.53213) (15588.23529 2224.88405) (15565.61086 2229.56312) (15478.88575 2268.93563) (15384.61538 2302.87229)
(15211.15950 2359.42647) (15037.70781 2405.58405) (14924.58563 2431.97896) (14905.73111 2432.27443) (14860.48224
2443.29118) (14837.85781 2443.58665) (14815.23337 2450.83292) (14626.69683 2466.06335) (14528.65803 2465.91561)
(14351.43247 2450.83292) (14230.76923 2431.97896) (14102.56369 2405.58405) (13978.12930 2374.51618) (13827.30057
2325.48982) (13646.30509 2257.47500) (13570.88948 2224.73631)))
("SF_PLANTING" 0 ((13604.82613 3239.06459) (13574.66063 3239.06459)))
("SF_MASONRY_AND_ARCH" 0 ((13585.97285 1172.70079) (13585.96595 1342.38405) (13578.43869 1391.40271) (13578.43133
2111.61414) (13578.43133 2138.00905)))
("SF_PLANTING" 0 ((13578.43179 3800.90498) (13612.36844 3800.90498)))
("SF_PLANTING" 0 ((13589.74400 3751.88495) (13582.35633 3763.19785) (13578.43179 3800.90498)))
("SF_PLANTING" 0 ((13578.43179 3665.15837) (13576.91425 3657.61041) (13593.36606 3631.22172) (13593.36606 3589.75023)
(13589.74400 3582.20238)))
("SF_SOLAR" 0 ((13582.20170 8118.40113) (13593.51391 8133.48416)))
("SF_SOLAR" 0 ((13585.97285 7982.65452) (13597.28507 7997.73756)))
("SF_SOLAR" 0 ((13589.74400 7918.55204) (13585.97285 7929.86425)))
("SF_PLANTING" 0 ((13585.97285 1172.70079) (13612.36799 1172.70079)))
("SF_PLANTING" 0 ((13589.74400 3570.89016) (13589.74400 3582.20238)))
("SF_PLANTING" 0 ((13604.82613 3495.47511) (13604.98077 3529.41176) (13619.14864 3548.41346) (13608.59038 3562.29898)
(13589.74400 3570.89016)))
("SF_PLANTING" 0 ((13589.74400 324.28450) (13602.25351 384.61538) (13616.13835 407.23982)))
("SF_PLANTING" 0 ((13589.74400 324.28450) (13608.59729 328.05430)))
("SF_PLANTING" 0 ((13597.28507 3371.04072) (13593.51391 3359.72851)))
("SF_SOLAR" 0 ((13597.28507 8069.38167) (13604.82613 8084.46448)))
("SF_PLANTING" 0 ((13601.05622 1018.09955) (13611.16437 1006.79355) (13612.36844 999.24491)))
("SF_PLANTING" 0 ((13601.05622 1018.09955) (13617.19468 1059.57862) (13634.99287 1078.27715) (13646.30509 1082.20305)))
("SF_PLANTING" 0 ((13601.05622 444.94627) (13602.11267 429.86425) (13616.13835 407.23982)))
("SF_PLANTING" 0 ((13601.05622 444.94627) (13627.45057 493.96776)))
("SF_PLANTING" 0 ((13604.82613 3495.47511) (13638.76278 3469.08020)))
("SF_PLANTING" 0 ((13604.82613 3239.06459) (13642.53394 3239.06459)))
("SF_MASONRY_AND_ARCH" 0 ((13604.82613 3239.06459) (13604.81923 3035.44468) (13601.05622 3012.82025) (13604.82613
2960.03043)))
("SF_MASONRY_AND_ARCH" 0 ((13642.53394 2960.03043) (13604.82613 2960.03043)))
("SF_PLANTING" 0 ((13634.99287 938.91403) (13616.13835 939.06867) (13604.82613 946.45645)))
("SF_PLANTING" 0 ((13604.82613 946.45645) (13608.74502 995.32048) (13612.36844 999.24491)))
("SF_SOLAR" 0 ((13646.30509 8042.98643) (13608.59729 8042.98643)))
("SF_SOLAR" 0 ((13608.59729 7944.94717) (13619.90950 7941.17647)))
("SF_PLANTING" 0 ((13614.25339 3955.50486) (13608.81957 3963.05339) (13608.59729 3993.21267)))
("SF_PLANTING" 0 ((13608.59729 3993.21267) (13619.01471 4023.37195) (13627.45057 4030.92048)))
("SF_PLANTING" 0 ((13616.13835 3412.51912) (13606.92500 3446.44887) (13608.59729 3453.99672)))
("SF_PLANTING" 0 ((13612.36799 1172.70079) (13623.68756 1166.35633) (13638.76278 1165.15837)))
("SF_MASONRY_AND_ARCH" 0 ((13612.36844 2202.11188) (13608.60419 2190.79966) (13612.36799 2100.30192) (13612.36799
2077.67749) (13612.36799 1964.55532) (13612.36799 1945.70136) (13612.36799 1821.26697) (13612.36799 1798.64253)
(13612.36799 1383.86029) (13612.36799 1274.51075) (13612.36799 1255.65611) (13612.36799 1244.34389) (13612.36799
1172.70079)))
("SF_SOLAR" 0 ((13616.13835 8035.44502) (13612.36844 8027.90339)))
("SF_SOLAR" 0 ((13612.36844 7869.53247) (13627.45057 7869.53247)))
("SF_PLANTING" 0 ((13612.36844 3800.90498) (13623.68066 3785.82161)))
("SF_PLANTING" 0 ((13627.45057 3842.38269) (13622.62432 3819.75826) (13612.36844 3800.90498)))
("SF_PLANTING" 0 ((13612.36844 3672.69943) (13619.91640 3665.31301) (13642.53394 3665.15837)))
("SF_PLANTING" 0 ((13612.36844 999.24491) (13642.53394 994.27025) (13653.84615 984.16290)))
("SF_PLANTING" 0 ((13614.25339 3955.50486) (13623.61301 3949.16143) (13646.30509 3944.19265)))
("SF_PLANTING" 0 ((13614.25339 3955.50486) (13631.22172 3969.38371) (13653.84615 3974.35939)))
("SF_PLANTING" 0 ((13665.15837 322.39819) (13632.42590 346.90894) (13634.83824 388.38518) (13627.44502 399.69253)
(13616.13835 407.23982)))
("SF_PLANTING" 0 ((13616.13835 241.32636) (13634.99287 233.93382) (13653.84615 233.93450) (13680.24174 248.86878)))
("SF_PLANTING" 0 ((13616.13835 241.32636) (13619.90950 252.63857)))
("SF_SOLAR" 0 ((13619.90950 7922.32274) (13631.22172 7937.40577)))
("SF_SOLAR" 0 ((13623.68066 8114.63054) (13638.76278 8133.48416)))
("SF_ARCHITECTURE" 0 ((13627.45057 5531.67421) (13627.45057 4291.10147)))
("SF_ARCHITECTURE" 0 ((13627.45057 5531.67421) (13657.61731 5539.21527) (13687.78281 5539.06742) (13706.63609
5531.67421)))
("SF_PLANTING" 0 ((13631.22172 4079.93925) (13635.14072 4140.27149) (13646.15735 4196.83258) (13646.29819 4242.08145)
(13641.32975 4283.41131) (13627.45057 4291.10147)))
("SF_PLANTING" 0 ((13627.45057 4046.00260) (13627.45057 4030.92048)))
("SF_PLANTING" 0 ((13627.45057 4046.00260) (13631.22172 4079.93925)))
("SF_PLANTING" 0 ((13646.30509 4027.14932) (13627.45057 4030.92048)))
("SF_PLANTING" 0 ((13627.45057 3842.38269) (13631.22172 3861.23722)))
("SF_SOLAR" 0 ((13642.53394 7975.11312) (13631.22172 7975.11312)))
("SF_SOLAR" 0 ((13631.22172 7937.40577) (13643.58337 7963.79434) (13653.84615 7971.18767) (13876.31934 7971.34231)))
("SF_SOLAR" 0 ((13631.22172 7937.40577) (13804.67613 7937.41233) (13849.92500 7941.17647)))
("SF_PLANTING" 0 ((13687.78281 4110.10600) (13668.92262 4092.30814) (13646.30509 4080.99593) (13631.22172 4079.93925)))
("SF_PLANTING" 0 ((13717.94830 3872.54943) (13631.22172 3861.23722)))
("SF_MASONRY_AND_ARCH" 0 ((13631.22172 2202.11188) (13642.82941 2194.86629) (13642.52704 1515.83710) (13638.91052
1500.75509) (13638.76968 1421.56957) (13642.52704 1402.71493) (13642.54084 1217.94966) (13646.29819 1195.32523)
(13638.76278 1165.15837)))
("SF_PLANTING" 0 ((13661.38722 912.51980) (13653.83925 923.82443) (13634.99287 938.91403)))
("SF_PLANTING" 0 ((13634.99287 938.91403) (13643.73111 972.85068) (13653.84615 984.16290)))
("SF_PLANTING" 0 ((13638.76278 3906.48609) (13657.61731 3917.79830)))
("SF_PLANTING" 0 ((13638.76278 3714.17839) (13650.07500 3717.94830)))
("SF_PLANTING" 0 ((13638.76278 1165.15837) (13642.38620 1153.84615) (13642.68167 1101.06244) (13646.30509 1093.51527)))
("SF_SOLAR" 0 ((13642.53394 8073.15226) (13642.53394 8080.69389)))
("SF_SOLAR" 0 ((13642.53394 7888.38609) (13642.53394 7880.84468)))
("SF_PLANTING" 0 ((13642.53394 3665.15837) (13646.45984 3612.36776) (13657.61731 3597.28507)))
("SF_PLANTING" 0 ((13642.53394 3665.15837) (13650.07500 3717.94830)))
("SF_MASONRY_AND_ARCH" 0 ((13642.53394 2960.03043) (13642.54084 3076.92308) (13646.30509 3099.54751) (13642.53394
3239.06459)))
("SF_PLANTING" 0 ((13725.49061 3239.06459) (13672.69943 3242.83586) (13642.53394 3239.06459)))
("SF_MASONRY_AND_ARCH" 0 ((13642.53394 2960.03043) (13706.63609 2960.03043)))
("SF_SOLAR" 0 ((13661.38722 8005.27896) (13646.30509 8016.59118)))
("SF_SOLAR" 0 ((13646.30509 8016.59118) (13661.38722 8050.52783)))
("SF_PLANTING" 0 ((13702.86618 4023.37817) (13646.30509 4027.14932)))
("SF_PLANTING" 0 ((13653.84615 3974.35939) (13646.45294 4000.75373) (13646.30509 4027.14932)))
("SF_PLANTING" 0 ((13646.30509 1093.51527) (13646.30509 1082.20305)))
("SF_PLANTING" 0 ((13646.30509 1093.51527) (13657.61731 1099.85769) (13676.47059 1102.94118)))
("SF_PLANTING" 0 ((13672.69943 1078.43043) (13646.30509 1082.20305)))
("SF_PLANTING" 0 ((13680.24174 263.95079) (13646.30509 279.03563)))
("SF_PLANTING" 0 ((13665.15837 322.39819) (13651.27353 301.66007) (13646.30509 279.03563)))
("SF_PLANTING" 0 ((13672.69943 3725.49061) (13650.07500 3725.49061)))
("SF_PLANTING" 0 ((13650.07500 3725.49061) (13650.07500 3717.94830)))
("SF_PLANTING" 0 ((13650.07500 3725.49061) (13650.22274 3748.11505) (13658.67376 3770.73948) (13679.03767 3793.36391)
(13684.16629 3815.98835) (13699.08812 3829.86663) (13706.63609 3831.07048)))
("SF_PLANTING" 0 ((13653.84615 3974.35939) (13680.24174 3949.02048) (13699.09502 3944.19265)))
("SF_PLANTING" 0 ((13693.43891 1057.69231) (13672.69389 1038.15136) (13653.84615 1029.41176)))
("SF_PLANTING" 0 ((13680.24174 984.16290) (13653.84615 984.16290)))
("SF_SOLAR" 0 ((13657.61731 7978.88394) (13737.85928 8110.85973) (13765.91199 8144.79638) (13770.73948 8163.65000)))
("SF_SOLAR" 0 ((13661.38722 7926.09355) (13657.61731 7914.78133)))
("SF_PLANTING" 0 ((13657.61731 3597.28507) (13661.53495 3548.26572) (13669.98597 3510.55781) (13680.24174 3495.47511)))
("SF_PLANTING" 0 ((13684.01165 3623.68066) (13680.08710 3604.98145) (13657.61731 3597.28507)))
("SF_PLANTING" 0 ((13661.38722 912.51980) (13676.47059 912.51980)))
("SF_SOLAR" 0 ((13665.15837 8114.63054) (13672.69943 8129.71335)))
("SF_PLANTING" 0 ((13665.15837 322.39819) (13680.24174 320.51188)))
("SF_PLANTING" 0 ((13665.15837 322.39819) (13675.57579 361.99095) (13697.89785 392.15781) (13703.91572 407.08518)
(13710.40724 411.00962)))
("SF_SOLAR" 0 ((13668.92952 8039.21561) (13676.47059 8039.21561)))
("SF_PLANTING" 0 ((13699.09502 505.27998) (13668.92952 520.36199)))
("SF_SOLAR" 0 ((13680.24174 7960.03020) (13672.69943 7948.71799)))
("SF_PLANTING" 0 ((13672.69943 3725.49061) (13717.94830 3725.49061)))
("SF_PLANTING" 0 ((13672.69943 3725.49061) (13680.24174 3702.86618)))
("SF_PLANTING" 0 ((13672.69943 3725.49061) (13688.83914 3759.27885) (13705.43880 3770.88733) (13714.33314 3792.30724)
(13744.34389 3803.62568) (13774.50939 3808.44604)))
("SF_PLANTING" 0 ((13693.43891 1057.69231) (13672.69943 1078.43043)))
("SF_PLANTING" 0 ((13672.69943 1078.43043) (13676.47059 1102.94118)))
("SF_SOLAR" 0 ((13676.47059 7854.44943) (13680.24174 7888.38609)))
("SF_PLANTING" 0 ((13676.47059 1184.01301) (13676.47059 1233.03167)))
("SF_PLANTING" 0 ((13676.47059 1102.94118) (13681.44593 1131.07330) (13691.55396 1137.70701) (13706.63609 1138.76414)))
("SF_PLANTING" 0 ((13710.40724 1119.90950) (13695.17602 1106.03088) (13676.47059 1102.94118)))
("SF_PLANTING" 0 ((13785.82161 904.97738) (13751.88495 897.58337) (13714.17839 897.58337) (13676.47059 912.51980)))
("SF_PLANTING" 0 ((13680.24174 984.16290) (13680.09400 923.83201) (13676.47059 912.51980)))
("SF_MASONRY_AND_ARCH" 0 ((13680.24174 1255.65611) (13676.47749 1266.96833) (13676.47749 2096.53066) (13680.09400
2111.61414) (13680.39649 2179.48054) (13684.16629 2185.82432) (13695.32387 2187.02839)))
("SF_PLANTING" 0 ((13687.78281 984.16290) (13680.24174 984.16290)))
("SF_PLANTING" 0 ((13680.24174 305.42986) (13680.24174 320.51188)))
("SF_PLANTING" 0 ((13782.05170 380.84559) (13717.94830 349.62240) (13680.24174 320.51188)))
("SF_PLANTING" 0 ((13680.24174 305.42986) (13684.01165 297.88744)))
("SF_PLANTING" 0 ((13680.24174 305.42986) (13676.47059 305.42986) (13676.47059 301.66007) (13684.01165 297.88744)))
("SF_PLANTING" 0 ((13680.24174 263.95079) (13680.24174 248.86878)))
("SF_PLANTING" 0 ((13680.24174 263.95079) (13686.58563 271.50011) (13691.55396 290.34785)))
("SF_PLANTING" 0 ((13680.24174 248.86878) (13699.09502 237.70498) (13736.80283 241.32636)))
("SF_SOLAR" 0 ((13684.01165 8058.06946) (13691.55396 8058.06946)))
("SF_SOLAR" 0 ((13684.01165 8005.27896) (13751.88495 8012.81403) (13849.92500 8005.57511) (13902.71493 8012.82059)))
("SF_PLANTING" 0 ((13684.01165 3684.01165) (13696.38020 3650.07568) (13710.40724 3638.76278)))
("SF_MASONRY_AND_ARCH" 0 ((13706.63609 2624.43439) (13691.56086 2620.66369) (13684.01165 2620.66369)))
("SF_MASONRY_AND_ARCH" 0 ((13702.86618 2586.72726) (13685.21572 2601.80995) (13684.01165 2620.66369)))
("SF_PLANTING" 0 ((13684.01165 297.88744) (13691.55396 290.34785)))
("SF_PLANTING" 0 ((13687.78281 4294.87138) (13702.86618 4302.41369)))
("SF_PLANTING" 0 ((13719.83450 4096.90758) (13695.33077 4103.76154) (13687.78281 4110.10600)))
("SF_PLANTING" 0 ((13687.78281 4110.10600) (13688.83914 4132.73043) (13695.46606 4143.88767) (13702.86618 4147.81256)))
("SF_MASONRY_AND_ARCH" 0 ((13687.78281 3171.19129) (13687.78281 3178.73303)))
("SF_PLANTING" 0 ((13687.78281 984.16290) (13774.50939 961.53846)))
("SF_PLANTING" 0 ((13702.86618 1033.18156) (13696.37330 1029.25713) (13688.83224 1010.55713) (13687.78281 984.16290)))
("SF_SOLAR" 0 ((13691.55396 8099.54751) (13733.03167 8156.10860)))
("SF_MASONRY_AND_ARCH" 0 ((13702.86618 2662.14152) (13691.55396 2662.14152)))
("SF_MASONRY_AND_ARCH" 0 ((13691.55396 2549.01934) (13691.55396 2530.16618)))
("SF_MASONRY_AND_ARCH" 0 ((13921.56821 2533.93665) (13853.69491 2526.40113) (13706.63609 2526.40113) (13691.55396
2530.16618)))
("SF_MASONRY_AND_ARCH" 0 ((13695.32387 2432.12670) (13691.70181 2439.67466) (13691.55396 2473.60509)))
("SF_PLANTING" 0 ((13691.55396 290.34785) (13706.63609 290.34785)))
("SF_PLANTING" 0 ((13702.86618 1033.18156) (13701.59446 1048.33337) (13693.43891 1057.69231)))
("SF_PLANTING" 0 ((13693.43891 1057.69231) (13714.17839 1073.46267) (13729.26052 1074.66063)))
("SF_SOLAR" 0 ((13695.32387 8080.69389) (13702.86618 8073.15226)))
("SF_MASONRY_AND_ARCH" 0 ((13710.40724 1263.19853) (13706.63654 1459.27602) (13706.63654 1481.90045) (13706.63654
1527.14932) (13706.63654 1840.12093) (13706.63654 1855.20362) (13702.86572 1938.15962) (13702.86572 1953.24310)
(13702.86572 2130.46731) (13702.86572 2179.48054) (13695.32387 2187.02839)))
("SF_MASONRY_AND_ARCH" 0 ((13725.49061 2194.57014) (13702.86572 2193.51380) (13695.32387 2187.02839)))
("SF_PLANTING" 0 ((13725.49061 3887.63156) (13724.43428 3898.94446) (13704.06346 3925.33937) (13699.09502 3944.19265)))
("SF_PLANTING" 0 ((13699.09502 3944.19265) (13706.63609 3947.96380)))
("SF_MASONRY_AND_ARCH" 0 ((13702.86618 2586.72726) (13699.09502 2575.41505)))
("SF_MASONRY_AND_ARCH" 0 ((13699.09502 2390.64830) (13714.17839 2383.25577) (13793.36391 2380.53405) (13815.98835
2383.10735)))
("SF_PLANTING" 0 ((13699.09502 505.27998) (13702.86618 497.73756)))
("SF_PLANTING" 0 ((13706.63609 531.67421) (13699.09502 505.27998)))
("SF_PLANTING" 0 ((13702.86618 4147.81256) (13703.01403 4230.76923) (13710.40724 4257.16482) (13710.25260 4291.10079)
(13702.86618 4302.41369)))
("SF_ARCHITECTURE" 0 ((13706.63609 5531.67421) (13702.86618 4302.41369)))
("SF_PLANTING" 0 ((13719.83450 4096.90758) (13720.51527 4132.72353) (13702.86618 4147.81256)))
("SF_PLANTING" 0 ((13710.40724 3981.90045) (13710.25950 4000.75373) (13702.86618 4023.37817)))
("SF_PLANTING" 0 ((13706.63609 4030.92048) (13702.86618 4030.92048) (13702.86618 4023.37817)))
("SF_PLANTING" 0 ((13706.63609 4030.92048) (13702.86618 4023.37817)))
("SF_MASONRY_AND_ARCH" 0 ((13702.86618 2586.72726) (13721.71946 2586.72726)))
("SF_PLANTING" 0 ((13710.40724 1263.19853) (13703.01403 1248.11369) (13702.86618 1195.32523)))
("SF_PLANTING" 0 ((13702.86618 1033.18156) (13770.73948 1006.78733)))
("SF_SOLAR" 0 ((13706.63609 8099.54751) (13717.94830 8099.54751)))
("SF_SOLAR" 0 ((13706.63609 8042.98643) (13789.59276 8042.97986) (13812.21719 8039.21572) (13846.15385 8042.98643)
(13853.69491 8039.21561) (13891.40271 8042.98643)))
("SF_ARCHITECTURE" 0 ((13778.28054 5535.44536) (13766.96833 5539.06742) (13725.49061 5539.06742) (13706.63609
5531.67421)))
("SF_PLANTING" 0 ((13706.63609 4030.92048) (13736.80283 4023.52658) (13778.28054 4023.37817)))
("SF_PLANTING" 0 ((13706.63609 4030.92048) (13717.80045 4072.39819) (13719.83450 4096.90758)))
("SF_PLANTING" 0 ((13725.49061 3947.96380) (13706.63609 3947.96380)))
("SF_PLANTING" 0 ((13710.40724 3981.90045) (13706.78382 3974.35249) (13706.63609 3947.96380)))
("SF_MASONRY_AND_ARCH" 0 ((13706.63609 2960.03043) (13729.26052 2960.03043)))
("SF_MASONRY_AND_ARCH" 0 ((13721.71946 3012.82025) (13710.55498 3005.27240) (13703.92262 2993.96708) (13706.63609
2960.03043)))
("SF_PLANTING" 0 ((13710.40724 1119.90950) (13706.63609 1138.76414)))
("SF_PLANTING" 0 ((13766.96833 1161.38857) (13729.26052 1160.18371) (13706.63609 1138.76414)))
("SF_PLANTING" 0 ((13706.63609 290.34785) (13724.43428 271.48699) (13736.80283 241.32636)))
("SF_PLANTING" 0 ((13744.34389 324.28450) (13740.41799 316.88292) (13706.63609 290.34785)))
("SF_PLANTING" 0 ((13710.40724 3981.90045) (13729.10577 3976.93857) (13733.03167 3970.58824)))
("SF_PLANTING" 0 ((13721.71946 1210.40724) (13721.56482 1251.88631) (13710.40724 1263.19853)))
("SF_PLANTING" 0 ((13729.26052 1074.66063) (13728.20407 1101.05486) (13710.40724 1119.90950)))
("SF_PLANTING" 0 ((13710.40724 411.00962) (13729.25362 402.71606) (13736.80283 403.47002)))
("SF_PLANTING" 0 ((13710.40724 411.00962) (13714.17839 422.32183)))
("SF_SOLAR" 0 ((13717.94830 8061.84005) (13766.96833 8058.06946) (13793.36391 8061.83348) (13872.54943 8061.83348)
(13898.94378 8058.06946) (13936.65158 8061.84005)))
("SF_PLANTING" 0 ((13717.94830 3872.54943) (13725.49751 3861.24310) (13740.57274 3849.92500)))
("SF_PLANTING" 0 ((13717.94830 3872.54943) (13725.49061 3887.63156)))
("SF_PLANTING" 0 ((13733.03167 3702.86618) (13717.94830 3725.49061)))
("SF_PLANTING" 0 ((13717.94830 3725.49061) (13729.26052 3737.69740) (13755.65611 3744.34389)))
("SF_PLANTING" 0 ((13717.94830 471.34333) (13777.22421 399.69740) (13782.05170 380.84559)))
("SF_PLANTING" 0 ((13719.83450 4096.90758) (13778.28054 4106.33484)))
("SF_MASONRY_AND_ARCH" 0 ((13721.71946 3012.82025) (13728.06324 3005.27240) (13732.88394 2986.42534) (13729.26052
2960.03043)))
("SF_MASONRY_AND_ARCH" 0 ((13725.49061 3239.06459) (13725.34287 3186.27477) (13721.71946 3167.42081) (13725.48371
3069.38133) (13721.86719 3054.29864) (13721.71946 3012.82025)))
("SF_MASONRY_AND_ARCH" 0 ((13721.71946 2126.69683) (13729.26052 2168.17523)))
("SF_PLANTING" 0 ((13800.90498 3857.46606) (13785.82161 3871.34468) (13725.49061 3887.63156)))
("SF_PLANTING" 0 ((13725.49061 3627.45057) (13744.18925 3615.08258) (13755.65611 3597.28507)))
("SF_PLANTING" 0 ((13755.65611 3597.28507) (13736.80283 3575.87172) (13725.49061 3578.43111)))
("SF_PLANTING" 0 ((13725.49061 3239.06459) (13759.42726 3242.83586)))
("SF_MASONRY_AND_ARCH" 0 ((13932.88043 2635.74661) (13914.02715 2620.81855) (13872.54943 2628.19864) (13834.84163
2624.44061) (13793.36391 2628.19174) (13778.28054 2624.58213) (13725.49061 2624.43439)))
("SF_MASONRY_AND_ARCH" 0 ((13729.26052 2187.02839) (13725.49061 2194.57014)))
("SF_MASONRY_AND_ARCH" 0 ((13725.49061 2194.57014) (13740.57274 2201.95724) (13766.96833 2198.34061)))
("SF_SOLAR" 0 ((13729.26052 8133.48416) (13733.03167 8122.17195)))
("SF_ARCHITECTURE" 0 ((13789.59276 5720.21109) (13729.26052 5720.21109)))
("SF_PLANTING" 0 ((13755.65611 3597.28507) (13778.12590 3592.45814) (13781.89706 3582.20238) (13774.36154 3567.26742)
(13760.63145 3555.80045) (13741.76991 3510.55781) (13736.44106 3485.36708) (13729.26052 3484.16290)))
("SF_MASONRY_AND_ARCH" 0 ((13729.26052 2960.03043) (13763.19717 2960.03043)))
("SF_PLANTING" 0 ((13729.26052 1074.66063) (13766.96833 1074.66063)))
("SF_ARCHITECTURE" 0 ((13733.03167 5599.54751) (14193.06143 5599.54751)))
("SF_MASONRY_AND_ARCH" 0 ((13736.80238 2034.31369) (13736.80238 2032.42839) (13736.80238 2030.54299)))
("SF_MASONRY_AND_ARCH" 0 ((13736.80238 1817.49717) (13736.80238 1881.59853) (13736.80238 1900.45249) (13736.80238
1949.47183)))
("SF_MASONRY_AND_ARCH" 0 ((13736.80238 1659.12613) (13736.80238 1723.22681)))
("SF_MASONRY_AND_ARCH" 0 ((13736.80238 1534.69174) (13736.80238 1493.21267) (13736.80238 1478.13066) (13736.80238
1221.71946)))
("SF_SOLAR" 0 ((13748.11505 8141.02557) (13736.80283 8141.02557)))
("SF_PLANTING" 0 ((13804.67613 237.55656) (13778.28054 230.16256) (13736.80283 241.32636)))
("SF_PLANTING" 0 ((13748.11505 3386.12342) (13740.72738 3378.57557) (13740.57274 3344.64581)))
("SF_SOLAR" 0 ((13744.34389 8095.77670) (13755.65611 8103.31833)))
("SF_MASONRY_AND_ARCH" 0 ((13921.56821 2533.93665) (13928.80814 2571.64378) (13917.79830 2585.52308) (13857.46606
2590.49152) (13789.59276 2590.35000) (13766.96833 2586.72726) (13744.34389 2590.49774)))
("SF_PLANTING" 0 ((13778.28054 3959.27602) (13759.42726 3947.81572) (13748.11505 3932.88043)))
("SF_PLANTING" 0 ((13748.11505 3386.12342) (13760.62455 3431.37229) (13785.82161 3461.53846)))
("SF_PLANTING" 0 ((13804.67613 3416.28959) (13785.81606 3391.09876) (13748.11505 3386.12342)))
("SF_SOLAR" 0 ((13751.88495 8110.85973) (13755.65611 8103.31833)))
("SF_SOLAR" 0 ((13751.88495 8069.38167) (13755.65611 8080.69389)))
("SF_SOLAR" 0 ((13751.88495 7869.53247) (13800.90498 7869.53247)))
("SF_PLANTING" 0 ((13778.28054 4155.35486) (13751.88495 4151.58371)))
("SF_SOLAR" 0 ((13966.81708 8107.08891) (13951.73495 8106.93439) (13932.88043 8099.56075) (13914.02715 8103.31165)
(13887.63156 8099.55419) (13868.77828 8103.31176) (13755.65611 8103.31833)))
("SF_PLANTING" 0 ((13785.82161 3717.94830) (13755.65611 3744.34389)))
("SF_PLANTING" 0 ((13774.50939 3793.36391) (13760.48371 3770.73948) (13755.65611 3744.34389)))
("SF_PLANTING" 0 ((13755.65611 294.11765) (13752.18179 286.57036) (13759.42726 271.49321)))
("SF_SOLAR" 0 ((13759.42726 7982.65452) (13759.42726 7993.96674)))
("SF_SOLAR" 0 ((13759.42726 7956.25939) (13759.42726 7963.80090)))
("SF_PLANTING" 0 ((13759.42726 3676.47059) (13766.96833 3672.69943)))
("SF_PLANTING" 0 ((13759.42726 3242.83586) (13797.13382 3239.06459)))
("SF_MASONRY_AND_ARCH" 0 ((13759.42726 3242.83586) (13759.43416 3073.15260) (13763.18473 3054.29864) (13759.43416
3020.36199) (13763.04932 3005.27930) (13763.19717 2960.03043)))
("SF_PLANTING" 0 ((13766.96833 3646.30509) (13763.19717 3634.99287)))
("SF_MASONRY_AND_ARCH" 0 ((13797.13382 2960.03043) (13763.19717 2960.03043)))
("SF_PLANTING" 0 ((13766.96833 3672.69943) (13766.96833 3646.30509)))
("SF_PLANTING" 0 ((13766.96833 3672.69943) (13782.05170 3680.24174)))
("SF_PLANTING" 0 ((13800.90498 3657.61731) (13793.35701 3651.27285) (13766.96833 3646.30509)))
("SF_MASONRY_AND_ARCH" 0 ((13770.73948 2138.00905) (13763.35181 2149.32127) (13766.96833 2198.34061)))
("SF_MASONRY_AND_ARCH" 0 ((14355.20362 2360.48292) (14309.95475 2360.33518) (14294.87138 2356.71165) (14287.33032
2352.94118) (14245.85260 2349.02217) (14196.83258 2336.80204) (14177.97930 2326.70090) (14106.33484 2315.08631)
(13974.35939 2280.24095) (13891.40271 2253.85226) (13782.05170 2208.60339) (13766.96833 2198.34061)))
("SF_PLANTING" 0 ((13766.96833 1161.38857) (13766.96833 1074.66063)))
("SF_MASONRY_AND_ARCH" 0 ((13770.73948 2138.00905) (13766.97523 2122.92636) (13770.73258 2081.44796) (13770.73948
1180.24038) (13766.96833 1161.38857)))
("SF_PLANTING" 0 ((13770.73948 1067.11821) (13766.96833 1074.66063)))
("SF_SOLAR" 0 ((13770.73948 8163.65000) (14004.52489 8163.65000)))
("SF_MASONRY_AND_ARCH" 0 ((14570.13575 2307.69231) (14479.63801 2307.54457) (14351.43247 2296.23235) (14162.89593
2262.29570) (13955.50486 2201.05543) (13808.44604 2142.83597) (13770.73948 2138.00905)))
("SF_PLANTING" 0 ((13770.73948 1006.78733) (13774.50939 1029.41176) (13770.73948 1067.11821)))
("SF_PLANTING" 0 ((13823.52941 999.24491) (13812.36493 1021.86934) (13812.06256 1055.80600) (13808.29129 1063.34152)
(13797.13382 1070.72851) (13770.73948 1067.11821)))
("SF_PLANTING" 0 ((13770.73948 1006.78733) (13774.50939 1003.01753)))
("SF_PLANTING" 0 ((13770.73948 1006.78733) (13770.73948 1003.01753) (13774.50939 1003.01753)))
("SF_SOLAR" 0 ((13774.50939 8141.02557) (13883.86165 8141.03213) (13910.25600 8144.79638) (13966.81708 8144.64842)
(13978.12930 8141.02557)))
("SF_SOLAR" 0 ((13774.50939 8088.23529) (13793.36391 8088.23529)))
("SF_PLANTING" 0 ((13774.50939 3793.36391) (13774.50939 3808.44604)))
("SF_PLANTING" 0 ((13800.90498 3838.61278) (13778.43518 3819.75894) (13774.50939 3808.44604)))
("SF_PLANTING" 0 ((13774.50939 3793.36391) (13815.98835 3778.42862) (13838.61278 3778.28054)))
("SF_PLANTING" 0 ((13774.50939 961.53846) (13774.50939 1003.01753)))
("SF_PLANTING" 0 ((13785.82161 1006.78733) (13774.50939 1003.01753)))
("SF_PLANTING" 0 ((13785.82161 935.14423) (13774.50939 961.53846)))
("SF_SOLAR" 0 ((13782.05170 8197.58665) (13778.28054 8178.73303)))
("SF_SOLAR" 0 ((13778.28054 8024.13281) (13782.05170 8031.67421)))
("SF_ARCHITECTURE" 0 ((13778.28054 5101.80995) (13778.28054 5535.44536)))
("SF_ARCHITECTURE" 0 ((13778.28054 5535.44536) (13797.13382 5539.20905) (14494.72138 5539.22217) (14513.57466
5542.98020) (14543.74016 5539.21527) (15301.65724 5541.78880) (15354.45136 5539.06131) (15365.76357 5527.90351)))
("SF_ARCHITECTURE" 0 ((13778.28054 5101.80995) (13778.28054 5064.10215)))
("SF_ARCHITECTURE" 0 ((13778.28054 5101.80995) (13804.67613 5102.85973) (13932.88043 5153.54446) (13966.81708
5158.37104)))
("SF_ARCHITECTURE" 0 ((13778.28054 4155.35486) (13778.27364 4400.45249) (13770.73903 4419.30577) (13778.13281
4438.16029) (13778.27364 4517.34581) (13770.73903 4539.97025) (13770.73903 4766.21459) (13778.28054 4788.83903)
(13770.73903 4996.22885) (13778.13281 5011.31222) (13778.28054 5064.10215)))
("SF_ARCHITECTURE" 0 ((13978.12930 5143.28767) (13966.81708 5133.18020) (13951.73495 5130.77817) (13910.25600
5110.54921) (13895.17387 5108.15373) (13812.21719 5068.92308) (13778.28054 5064.10215)))
("SF_PLANTING" 0 ((13778.28054 4106.33484) (13778.28054 4155.35486)))
("SF_PLANTING" 0 ((13778.28054 4042.23269) (13778.28054 4106.33484)))
("SF_PLANTING" 0 ((13778.28054 4042.23269) (13812.21719 4042.23269)))
("SF_PLANTING" 0 ((13778.28054 4042.23269) (13778.28054 4023.37817)))
("SF_PLANTING" 0 ((13778.28054 3959.27602) (13774.80486 3970.58824) (13778.28054 4023.37817)))
("SF_PLANTING" 0 ((13778.28054 3959.27602) (13789.74740 3936.65781) (13804.67613 3925.33937)))
("SF_SOLAR" 0 ((13782.05170 8118.40113) (13793.36391 8133.48416)))
("SF_PLANTING" 0 ((13800.90498 3657.61731) (13789.44502 3676.31595) (13782.05170 3680.24174)))
("SF_PLANTING" 0 ((13785.82161 3695.32387) (13782.05170 3680.24174)))
("SF_PLANTING" 0 ((13815.98835 350.67873) (13808.58824 354.60385) (13789.45192 379.64072) (13782.05170 380.84559)))
("SF_SOLAR" 0 ((13846.15385 7895.92760) (13848.86176 7877.07387) (13834.68699 7844.19355) (13823.52941 7839.51459)
(13785.82161 7839.36652)))
("SF_PLANTING" 0 ((13785.82161 3717.94830) (13785.82161 3695.32387)))
("SF_PLANTING" 0 ((13842.38269 3725.49061) (13834.83473 3729.11267) (13800.90498 3729.10656) (13785.82161 3717.94830)))
("SF_PLANTING" 0 ((13829.18552 3682.12670) (13812.21719 3694.26776) (13785.82161 3695.32387)))
("SF_PLANTING" 0 ((13785.82161 935.14423) (13815.98835 933.93937) (13834.84163 916.28959)))
("SF_PLANTING" 0 ((13785.82161 935.14423) (13785.82161 904.97738)))
("SF_PLANTING" 0 ((13785.82161 904.97738) (13819.75826 905.13201) (13834.84163 916.28959)))
("SF_ARCHITECTURE" 0 ((13789.59276 5720.21109) (13800.90498 5710.10294) (13906.48609 5709.05351) (13921.56821
5720.21109)))
("SF_ARCHITECTURE" 0 ((13789.59276 5720.21109) (13804.67613 5734.08959) (13887.63156 5735.14604) (13910.25600
5730.31912) (13921.56821 5720.21109)))
("SF_PLANTING" 0 ((13789.59276 3472.85068) (13819.75826 3480.39242)))
("SF_PLANTING" 0 ((13797.13382 3423.83133) (13804.67613 3416.28959)))
("SF_PLANTING" 0 ((13823.52941 3355.95803) (13826.10339 3329.56233) (13823.16075 3315.68382) (13804.68303 3310.55452)
(13798.33790 3303.16742) (13797.13382 3291.85520)))
("SF_PLANTING" 0 ((13823.52941 3239.06459) (13797.13382 3239.06459)))
("SF_PLANTING" 0 ((13800.90498 3197.58699) (13797.28156 3205.13484) (13797.13382 3239.06459)))
("SF_MASONRY_AND_ARCH" 0 ((13831.07048 2960.03043) (13830.02093 3058.06912) (13823.37477 3071.94842) (13797.13382
3073.15260)))
("SF_MASONRY_AND_ARCH" 0 ((13797.13382 2960.03043) (13797.13382 3073.15260)))
("SF_MASONRY_AND_ARCH" 0 ((13800.90498 3197.58699) (13793.37081 3159.87907) (13797.13382 3073.15260)))
("SF_MASONRY_AND_ARCH" 0 ((13797.13382 2960.03043) (13831.07048 2960.03043)))
("SF_SOLAR" 0 ((13800.90498 7960.03020) (13797.13382 7956.25939) (13800.90498 7952.48869)))
("SF_PLANTING" 0 ((13800.90498 3857.46606) (13800.90498 3838.61278)))
("SF_PLANTING" 0 ((13800.90498 3857.46606) (13808.44604 3865.00713) (13808.44604 3872.54943)))
("SF_PLANTING" 0 ((13842.38269 3812.21719) (13800.90498 3838.61278)))
("SF_PLANTING" 0 ((13800.90498 3657.61731) (13819.75826 3657.61731)))
("SF_PLANTING" 0 ((13800.90498 3197.58699) (13819.60351 3208.90543) (13831.07048 3235.29412)))
("SF_SOLAR" 0 ((13804.67613 8031.67421) (13808.44604 8020.36199)))
("SF_SOLAR" 0 ((13808.44604 7993.96674) (13804.67613 7990.19615) (13804.67613 7978.88394)))
("SF_PLANTING" 0 ((13863.12217 3904.59989) (13838.61278 3920.51900) (13804.67613 3925.33937)))
("SF_PLANTING" 0 ((13808.44604 3872.54943) (13804.67613 3925.33937)))
("SF_PLANTING" 0 ((13804.67613 3544.49446) (13819.75826 3544.49446)))
("SF_PLANTING" 0 ((13815.98835 3416.28959) (13804.67613 3416.28959)))
("SF_PLANTING" 0 ((13808.44604 1153.84615) (13804.67613 1161.38857)))
("SF_PLANTING" 0 ((13876.31934 516.59219) (13838.61278 512.83337) (13804.67613 516.59219)))
("SF_PLANTING" 0 ((13891.40271 248.86878) (13868.77828 230.16946) (13838.61278 230.16256) (13804.67613 237.55656)))
("SF_PLANTING" 0 ((13804.67613 237.55656) (13815.98835 350.67873)))
("SF_PLANTING" 0 ((13863.12217 3904.59989) (13846.14695 3881.28812) (13808.44604 3872.54943)))
("SF_PLANTING" 0 ((13812.21719 4042.23269) (13831.07048 4015.98518) (13842.38269 4009.35215) (13853.69491 4008.29604)))
("SF_PLANTING" 0 ((13812.21719 4042.23269) (13827.30057 4064.85713)))
("SF_PLANTING" 0 ((13815.98835 3416.28959) (13823.38167 3393.66516) (13823.52941 3355.95803)))
("SF_PLANTING" 0 ((13815.98835 3416.28959) (13827.15283 3438.91403) (13827.14593 3461.53846) (13819.75826 3480.39242)))
("SF_PLANTING" 0 ((13815.98835 972.85068) (13817.04480 987.93269) (13823.52941 999.24491)))
("SF_PLANTING" 0 ((13853.69491 395.92760) (13838.45814 365.76075) (13815.98835 350.67873)))
("SF_PLANTING" 0 ((13827.30057 3582.20238) (13819.90600 3623.68066) (13819.75826 3657.61731)))
("SF_PLANTING" 0 ((13829.18552 3682.12670) (13826.10339 3665.16459) (13819.75826 3657.61731)))
("SF_PLANTING" 0 ((13819.75826 3544.49446) (13823.52941 3518.09955)))
("SF_PLANTING" 0 ((13827.30057 3582.20238) (13819.75826 3544.49446)))
("SF_PLANTING" 0 ((13838.61278 3548.26572) (13819.75826 3544.49446)))
("SF_PLANTING" 0 ((13823.52941 3495.47511) (13823.52941 3484.16290) (13819.75826 3480.39242)))
("SF_SOLAR" 0 ((13823.52941 7918.55204) (13823.52941 7929.86425)))
("SF_PLANTING" 0 ((13823.52941 3355.95803) (13831.07048 3355.95803)))
("SF_PLANTING" 0 ((13823.52941 3269.23077) (13823.52941 3239.06459)))
("SF_PLANTING" 0 ((13823.52941 3239.06459) (13831.07048 3235.29412)))
("SF_PLANTING" 0 ((13823.52941 999.24491) (13842.38269 999.24491)))
("SF_SOLAR" 0 ((13827.30057 8133.48416) (13827.30057 8118.40113)))
("SF_SOLAR" 0 ((13827.30057 8069.38167) (13827.30057 8084.46448)))
("SF_SOLAR" 0 ((13827.30057 7960.03020) (13831.07048 7952.48869)))
("SF_PLANTING" 0 ((13827.30057 3582.20238) (13846.15385 3574.51222) (13865.00713 3552.03620)))
("SF_MASONRY_AND_ARCH" 0 ((13857.46606 3152.33812) (13831.22511 3144.64174) (13827.30057 3122.17195)))
("SF_PLANTING" 0 ((13829.18552 3682.12670) (13849.92500 3672.69943)))
("SF_PLANTING" 0 ((13829.18552 3682.12670) (13842.38269 3714.17839)))
("SF_PLANTING" 0 ((13831.07048 3235.29412) (13849.92500 3235.29412)))
("SF_MASONRY_AND_ARCH" 0 ((13831.07048 2960.03043) (13846.15385 2956.25916) (13865.00713 2960.03043)))
("SF_MASONRY_AND_ARCH" 0 ((13842.38269 2269.98518) (13834.84163 2269.98518)))
("SF_PLANTING" 0 ((13846.15385 916.28959) (13834.84163 916.28959)))
("SF_PLANTING" 0 ((13838.61278 3778.28054) (13853.69491 3748.11505)))
("SF_PLANTING" 0 ((13842.38269 3812.21719) (13838.76063 3804.66923) (13838.61278 3778.28054)))
("SF_PLANTING" 0 ((13838.61278 452.48869) (13853.69491 395.92760)))
("SF_PLANTING" 0 ((13842.38269 3812.21719) (13857.46606 3812.21719)))
("SF_PLANTING" 0 ((13842.38269 3725.49061) (13842.38269 3714.17839)))
("SF_PLANTING" 0 ((13842.38269 3725.49061) (13853.69491 3748.11505)))
("SF_PLANTING" 0 ((13914.02715 3676.47059) (13891.40271 3681.43903) (13842.38269 3714.17839)))
("SF_MASONRY_AND_ARCH" 0 ((13853.69491 1504.52489) (13838.61233 1515.83710) (13838.61233 1534.69174) (13838.61233
1564.85577) (13838.61233 1583.71041) (13838.61233 2092.75328) (13842.38269 2100.30192)))
("SF_PLANTING" 0 ((13842.38269 999.24491) (13846.14695 976.62048) (13842.53733 935.14910) (13849.92500 927.60181)))
("SF_PLANTING" 0 ((13857.46606 1036.95419) (13850.97455 1025.64197) (13848.72783 1006.79423) (13842.38269 999.24491)))
("SF_SOLAR" 0 ((13849.92500 8031.67421) (13846.15385 8020.36199)))
("SF_SOLAR" 0 ((13846.15385 7956.25939) (13846.15385 7963.80090)))
("SF_PLANTING" 0 ((13974.35939 901.20758) (13880.09050 897.58337) (13861.23722 902.41097) (13846.15385 916.28959)))
("SF_PLANTING" 0 ((13846.15385 916.28959) (13849.92500 927.60181)))
("SF_SOLAR" 0 ((13849.92500 8118.40113) (13849.92500 8125.94276)))
("SF_SOLAR" 0 ((13849.92500 8088.23529) (13849.92500 8069.38167)))
("SF_SOLAR" 0 ((13849.92500 7986.42534) (13849.92500 7993.96674)))
("SF_SOLAR" 0 ((13872.54943 7843.13722) (13849.92500 7843.13722)))
("SF_MASONRY_AND_ARCH" 0 ((13857.46606 3152.33812) (13857.31833 3190.04525) (13849.92500 3235.29412)))
("SF_PLANTING" 0 ((13887.63156 3235.29412) (13872.54943 3239.06459) (13849.92500 3235.29412)))
("SF_PLANTING" 0 ((13883.86165 950.22624) (13849.92500 927.60181)))
("SF_PLANTING" 0 ((13863.12217 3904.59989) (13864.85928 3959.27602) (13853.69491 4008.29604)))
("SF_ARCHITECTURE" 0 ((13853.69491 4008.29604) (13861.23676 4023.37817) (13861.23676 4068.62704) (13858.67025
5007.53484) (13865.01403 5013.87862) (14038.46154 5078.13575) (14200.60373 5120.51538) (14362.74468 5146.91075)
(14445.70136 5154.45204) (14570.13575 5158.37104)))
("SF_PLANTING" 0 ((13876.31934 3751.88495) (13853.69491 3748.11505)))
("SF_PLANTING" 0 ((13857.46606 3303.16742) (13853.69491 3284.31346)))
("SF_MASONRY_AND_ARCH" 0 ((13853.69491 1504.52489) (13872.54898 1504.52489)))
("SF_PLANTING" 0 ((13853.69491 1504.52489) (13838.61233 1489.44287) (13838.61233 1308.44740) (13846.14695 1289.59276)
(13846.30848 1055.81357) (13857.46606 1044.49378)))
("SF_PLANTING" 0 ((13898.94378 422.32183) (13887.62602 407.38756) (13872.54943 397.12557) (13853.69491 395.92760)))
("SF_PLANTING" 0 ((13857.46606 3812.21719) (13868.77828 3805.73156) (13898.94378 3800.90498)))
("SF_PLANTING" 0 ((13857.46606 3812.21719) (13872.69729 3838.60588) (13897.88733 3857.61414) (13906.48609 3880.09050)))
("SF_MASONRY_AND_ARCH" 0 ((13857.46606 3152.33812) (13861.08948 3144.78948) (13861.24966 2997.73756) (13865.00713
2960.03043)))
("SF_PLANTING" 0 ((13857.46606 1036.95419) (13857.46606 1044.49378)))
("SF_PLANTING" 0 ((13857.46606 1044.49378) (13883.86165 1048.26640)))
("SF_PLANTING" 0 ((13857.46606 1036.95419) (13868.62364 1029.40486) (13876.47398 1015.38541) (13887.63156 1010.55713)))
("SF_PLANTING" 0 ((13914.02715 3676.47059) (13906.64084 3646.30509) (13917.64367 3619.90950) (13912.97081 3604.83303)
(13898.94378 3597.29197) (13861.23722 3604.82681)))
("SF_PLANTING" 0 ((13891.40271 248.86878) (13875.42443 267.72342) (13871.35090 294.11765) (13861.23722 309.19966)))
("SF_PLANTING" 0 ((13863.12217 3904.59989) (13906.48609 3902.71493)))
("SF_PLANTING" 0 ((13898.94378 3499.24559) (13901.51776 3525.64129) (13891.25498 3539.67455) (13865.00713 3552.03620)))
("SF_PLANTING" 0 ((13872.54943 3472.85068) (13861.38507 3525.64129) (13861.38507 3548.11109) (13865.00713 3552.03620)))
("SF_MASONRY_AND_ARCH" 0 ((13891.40271 2960.03043) (13865.00713 2960.03043)))
("SF_MASONRY_AND_ARCH" 0 ((13876.31934 2281.29740) (13865.00713 2281.29740)))
("SF_PLANTING" 0 ((13872.54898 1504.52489) (13880.08360 1493.21267) (13880.09740 1217.94966) (13883.86165 1195.32523)
(13880.09740 1074.66063) (13883.86165 1063.34842)))
("SF_MASONRY_AND_ARCH" 0 ((13872.54898 1504.52489) (13872.54898 1628.95928) (13880.09050 1651.58371) (13872.54898
1772.24830) (13880.08360 1791.10011) (13883.86165 2051.28179)))
("SF_SOLAR" 0 ((13872.54943 8069.38167) (13880.09050 8088.23529)))
("SF_SOLAR" 0 ((13876.31934 8031.67421) (13872.54943 8020.36199)))
("SF_SOLAR" 0 ((14494.72138 7888.38609) (14472.09695 7903.31448) (14170.43699 7903.32104) (14151.59061 7895.77296)
(14128.81154 7862.13903) (14113.87590 7854.59751) (13944.19265 7850.68529) (13883.86165 7855.65373) (13873.75362
7865.76176) (13872.54943 7892.15690)))
("SF_PLANTING" 0 ((13880.09050 3650.07500) (13872.54943 3657.61731)))
("SF_PLANTING" 0 ((13876.31934 3751.88495) (13887.63156 3741.62319) (13925.33937 3733.03167)))
("SF_PLANTING" 0 ((13876.31934 3751.88495) (13891.54355 3774.35543) (13898.94378 3778.28054)))
("SF_SOLAR" 0 ((13880.09050 8129.71335) (13883.86165 8125.94276) (13883.86165 8114.63054)))
("SF_PLANTING" 0 ((13898.94378 422.32183) (13890.34638 444.79299) (13880.09050 448.71889)))
("SF_PLANTING" 0 ((13887.63156 3412.51912) (13883.86165 3423.83133)))
("SF_MASONRY_AND_ARCH" 0 ((13895.17342 2088.98971) (13880.09740 2087.78552) (13872.54898 2081.44106) (13872.54898
2058.83043) (13883.86165 2051.28179)))
("SF_MASONRY_AND_ARCH" 0 ((13895.17342 2077.67749) (13883.86165 2051.28179)))
("SF_PLANTING" 0 ((13883.86165 1048.26640) (13883.86165 1063.34842)))
("SF_PLANTING" 0 ((13902.71493 1067.11821) (13883.86165 1063.34842)))
("SF_PLANTING" 0 ((13887.63156 1010.55713) (13895.32862 1029.55950) (13883.86165 1048.26640)))
("SF_PLANTING" 0 ((13883.86165 950.22624) (13891.40962 946.60351) (13914.02715 946.45645)))
("SF_PLANTING" 0 ((13883.86165 950.22624) (13887.63156 961.53846)))
("SF_MASONRY_AND_ARCH" 0 ((13887.63156 3235.29412) (13887.63846 3024.13247) (13891.25498 3009.04977) (13891.40271
2960.03043)))
("SF_PLANTING" 0 ((13925.33937 3239.06459) (13895.18077 3238.91686) (13887.63156 3235.29412)))
("SF_PLANTING" 0 ((13887.63156 1010.55713) (13891.40271 980.39310)))
("SF_PLANTING" 0 ((13887.63156 346.90894) (13896.22342 297.88744) (13914.02715 275.26301)))
("SF_MASONRY_AND_ARCH" 0 ((13891.40271 2960.03043) (13906.48609 2956.25916) (13925.33937 2960.03043)))
("SF_MASONRY_AND_ARCH" 0 ((13891.40271 2292.60962) (13917.79830 2297.57726) (13959.27602 2314.17760) (14076.16934
2348.12115) (14196.83258 2375.41787) (14374.05690 2401.81278) (14513.57466 2413.26652) (14683.25792 2409.35452)
(14826.54559 2394.27183) (14879.33676 2383.25509) (14920.81448 2382.95962) (14973.60441 2371.94287) (14992.45894
2371.64740) (15086.72658 2348.11425) (15203.61991 2311.46278) (15211.15950 2307.69231) (15263.95362 2292.60962)))
("SF_PLANTING" 0 ((13891.40271 248.86878) (13910.25600 248.86878)))
("SF_MASONRY_AND_ARCH" 0 ((13895.17342 2077.67749) (13895.17342 2088.98971)))
("SF_MASONRY_AND_ARCH" 0 ((13895.17342 2088.98971) (13906.48609 2100.14027) (13921.56821 2092.76018)))
("SF_MASONRY_AND_ARCH" 0 ((13895.17342 2077.67749) (13913.87941 2082.65215) (13921.56821 2092.76018)))
("SF_PLANTING" 0 ((13898.94378 3789.59276) (13898.94378 3800.90498)))
("SF_PLANTING" 0 ((13985.67161 3831.07048) (13955.50486 3834.54514) (13917.79830 3829.86663) (13907.68337 3819.75826)
(13898.94378 3800.90498)))
("SF_PLANTING" 0 ((13898.94378 3789.59276) (13898.94378 3778.28054)))
("SF_PLANTING" 0 ((13936.65158 3800.90498) (13914.02715 3790.64943) (13898.94378 3789.59276)))
("SF_PLANTING" 0 ((13925.33937 3748.11505) (13906.34389 3774.35543) (13898.94378 3778.28054)))
("SF_PLANTING" 0 ((13940.42274 433.63405) (13925.33937 422.47715) (13898.94378 422.32183)))
("SF_ARCHITECTURE" 0 ((13906.48609 3989.44152) (13902.72183 4000.75441) (13902.72183 4238.31029) (13906.47919
4257.16482) (13902.71493 4306.18360) (13906.47919 4479.63801) (13902.71493 4517.34581) (13906.47919 4539.97025)
(13906.48609 4898.19005) (13902.71493 4943.43891)))
("SF_ARCHITECTURE" 0 ((13917.79830 4973.60441) (13902.72183 4972.40057) (13896.37805 4966.05713) (13896.37115
4950.98688) (13902.71493 4943.43891)))
("SF_ARCHITECTURE" 0 ((13917.79785 4962.29219) (13902.71493 4943.43891)))
("SF_SOLAR" 0 ((13906.48609 7903.46912) (14144.04265 7903.46912)))
("SF_PLANTING" 0 ((13906.48609 3902.71493) (13906.33835 3970.58824) (13903.01041 3981.89423) (13906.48609 3989.44152)))
("SF_PLANTING" 0 ((13906.48609 3989.44152) (13932.88043 3993.05803) (13955.50486 3978.12930)))
("SF_PLANTING" 0 ((13906.48609 3902.71493) (13906.48609 3880.09050)))
("SF_PLANTING" 0 ((13968.70328 3889.51776) (13955.50894 3880.24830) (13906.48609 3880.09050)))
("SF_PLANTING" 0 ((13910.25600 248.86878) (13917.80520 237.71120) (13925.33937 233.94005) (13963.04717 233.93450)
(13978.12930 241.32636)))
("SF_PLANTING" 0 ((13910.25600 248.86878) (13914.02715 275.26301)))
("SF_SOLAR" 0 ((13917.79830 8073.15226) (13917.79830 8084.46448) (13914.02715 8088.23529)))
("SF_PLANTING" 0 ((13914.02715 3676.47059) (13929.11052 3699.09502)))
("SF_PLANTING" 0 ((13914.02715 946.45645) (13915.23133 961.53156) (13929.11052 969.08088)))
("SF_PLANTING" 0 ((13914.02715 946.45645) (13932.88043 946.60973) (13944.19265 953.99604)))
("SF_PLANTING" 0 ((13963.04717 290.34785) (13947.96380 289.29072) (13932.88043 280.23281) (13914.02715 275.26301)))
("SF_ARCHITECTURE" 0 ((13917.79785 4962.29219) (13917.79830 4973.60441)))
("SF_ARCHITECTURE" 0 ((13917.79785 4962.29219) (13940.41584 4967.26097) (13947.96380 4973.60441)))
("SF_SOLAR" 0 ((13917.79830 8133.48416) (13917.79830 8118.40113)))
("SF_ARCHITECTURE" 0 ((13947.96380 4984.91663) (13925.34627 4983.71278) (13917.79830 4973.60441)))
("SF_PLANTING" 0 ((13929.11052 343.13631) (13917.79830 316.74208)))
("SF_ARCHITECTURE" 0 ((13993.21267 5720.21109) (13921.56821 5720.21109)))
("SF_MASONRY_AND_ARCH" 0 ((13921.56821 2533.93665) (13955.50486 2530.01765) (13978.12930 2522.63066) (14144.04265
2522.63066) (14159.12477 2526.39491)))
("SF_MASONRY_AND_ARCH" 0 ((13921.56821 2119.15509) (13936.65158 2104.07240)))
("SF_MASONRY_AND_ARCH" 0 ((13921.56821 2092.76018) (13936.65158 2104.07240)))
("SF_PLANTING" 0 ((13925.33937 3748.11505) (13925.33937 3733.03167)))
("SF_PLANTING" 0 ((13925.33937 3748.11505) (13955.50486 3759.42726)))
("SF_PLANTING" 0 ((13929.11052 3699.09502) (13925.33937 3733.03167)))
("SF_PLANTING" 0 ((13925.33937 3239.06459) (13951.72805 3238.91686) (13959.27602 3235.29412)))
("SF_MASONRY_AND_ARCH" 0 ((13925.33937 3239.06459) (13925.33937 2960.03043)))
("SF_MASONRY_AND_ARCH" 0 ((13925.33937 2960.03043) (13955.50486 2960.03043)))
("SF_PLANTING" 0 ((13929.11052 3699.09502) (13944.19265 3695.32387)))
("SF_MASONRY_AND_ARCH" 0 ((14136.50034 2665.91256) (14113.87590 2665.91256) (13936.65848 2665.91256) (13929.11052
2665.91278)))
("SF_PLANTING" 0 ((13929.11052 1078.43043) (13940.42274 1085.97285) (13940.42274 1089.74265)))
("SF_PLANTING" 0 ((13929.11052 969.08088) (13944.19265 953.99604)))
("SF_PLANTING" 0 ((13963.04717 1089.74265) (13977.98145 1078.42557) (13984.61527 1067.11821) (13980.69627 1025.64683)
(13974.35249 1019.30441) (13951.73495 1017.94491) (13940.57749 1010.55226) (13929.11052 969.08088)))
("SF_SOLAR" 0 ((14159.12477 7937.40577) (14046.00260 7937.41233) (14023.37817 7941.17647) (13955.50486 7941.02839)
(13936.65158 7937.40577)))
("SF_MASONRY_AND_ARCH" 0 ((13936.65158 2134.23857) (13944.19955 2133.03439) (13963.04717 2115.38462)))
("SF_MASONRY_AND_ARCH" 0 ((13963.04717 2115.38462) (13955.49796 2109.03394) (13936.65158 2104.07240)))
("SF_PLANTING" 0 ((13940.42274 433.63405) (13936.65158 490.19514)))
("SF_SOLAR" 0 ((13940.42274 8133.48416) (13940.42274 8118.40113)))
("SF_PLANTING" 0 ((13968.70328 3889.51776) (13940.42274 3925.33937)))
("SF_PLANTING" 0 ((13940.42274 433.63405) (13970.58133 439.96538) (13976.92511 433.62919) (13978.12930 418.55204)))
("SF_PLANTING" 0 ((13951.73495 953.99604) (13944.19265 953.99604)))
("SF_ARCHITECTURE" 0 ((13947.96380 4984.91663) (13947.96380 4973.60441)))
("SF_ARCHITECTURE" 0 ((13947.96380 4984.91663) (13955.51176 4995.02500) (13978.12930 4996.22885)))
("SF_ARCHITECTURE" 0 ((13978.12930 4996.22885) (13966.81154 4978.57319) (13947.96380 4973.60441)))
("SF_PLANTING" 0 ((13947.96380 3797.13382) (13959.27602 3797.13382) (13963.04717 3793.36391)))
("SF_PLANTING" 0 ((13974.35939 935.14423) (13951.73495 953.99604)))
("SF_PLANTING" 0 ((13951.73495 953.99604) (13974.35939 971.65271) (14004.52489 972.85068)))
("SF_SOLAR" 0 ((13955.50486 7929.86425) (13955.50486 7914.78133)))
("SF_PLANTING" 0 ((14015.83710 3748.11505) (14000.75373 3748.26290) (13955.50486 3759.42726)))
("SF_PLANTING" 0 ((13963.04717 3793.36391) (13955.50486 3759.42726)))
("SF_MASONRY_AND_ARCH" 0 ((13985.67161 2960.03043) (13955.50486 2960.03043)))
("SF_MASONRY_AND_ARCH" 0 ((13955.50486 2960.03043) (13959.27602 3235.29412)))
("SF_SOLAR" 0 ((13959.27602 7975.11312) (13981.90045 7971.34887) (14196.83258 7971.34231)))
("SF_PLANTING" 0 ((13959.27602 4034.69038) (13966.96618 4019.60826) (14003.46855 3981.90045) (14012.06595 3959.27602)))
("SF_PLANTING" 0 ((13996.98382 3239.06459) (13959.27602 3235.29412)))
("SF_PLANTING" 0 ((13989.44152 3800.90498) (13963.04717 3793.36391)))
("SF_PLANTING" 0 ((14027.14932 3672.69943) (13985.67161 3670.12681) (13963.04717 3680.24174)))
("SF_MASONRY_AND_ARCH" 0 ((13993.21267 2126.69683) (13985.66471 2120.34615) (13963.04717 2115.38462)))
("SF_PLANTING" 0 ((13963.04717 403.47002) (13955.65950 324.28450) (13966.81708 309.19966)))
("SF_PLANTING" 0 ((13963.04717 290.34785) (13973.15532 279.03563) (13978.12930 241.32636)))
("SF_PLANTING" 0 ((13966.81708 309.19966) (13963.04717 290.34785)))
("SF_ARCHITECTURE" 0 ((13966.81708 5158.37104) (13978.12930 5143.28767)))
("SF_ARCHITECTURE" 0 ((14004.52489 5173.45441) (13970.74287 5164.72138) (13966.81708 5158.37104)))
("SF_MASONRY_AND_ARCH" 0 ((13966.81708 2466.06335) (13966.97172 2439.67466) (13974.35939 2432.12670)))
("SF_MASONRY_AND_ARCH" 0 ((13966.81708 2145.55079) (13977.98145 2144.34661) (13993.21267 2126.69683)))
("SF_PLANTING" 0 ((14008.29604 320.51188) (13996.98382 314.02794) (13966.81708 309.19966)))
("SF_PLANTING" 0 ((13968.70328 3889.51776) (13981.89774 3881.14966) (14004.52489 3880.09050)))
("SF_PLANTING" 0 ((13968.70328 3889.51776) (13977.07014 3902.71188) (13990.49785 3944.18643) (14012.06595 3959.27602)))
("SF_MASONRY_AND_ARCH" 0 ((13970.58824 2575.41505) (13993.21267 2579.18552) (14015.83710 2575.42127) (14095.02262
2575.41505)))
("SF_SOLAR" 0 ((13978.12930 7963.80090) (13974.35939 7956.25939)))
("SF_PLANTING" 0 ((13974.35939 901.20758) (13974.35939 935.14423)))
("SF_PLANTING" 0 ((13974.35939 935.14423) (13989.44152 935.29751) (14004.52489 942.68382)))
("SF_PLANTING" 0 ((13974.35939 901.20758) (13985.67161 897.58337) (14023.37817 897.59027) (14042.23269 912.51980)))
("SF_SOLAR" 0 ((14257.16482 8050.52783) (14230.76923 8016.74593) (14204.37364 8009.19774) (14136.50034 8009.19774)
(14121.41821 8012.80747) (14106.33484 8009.19774) (14012.06595 8009.04321) (13978.12930 8005.27896)))
("SF_ARCHITECTURE" 0 ((14012.06595 5154.59989) (14008.14140 5148.25645) (13978.12930 5143.28767)))
("SF_ARCHITECTURE" 0 ((13978.12930 4996.22885) (13993.21267 4997.27930) (14125.18812 5040.42229) (14230.76923
5063.95430) (14358.97477 5086.57873) (14479.63801 5094.26889)))
("SF_PLANTING" 0 ((14049.77376 237.55656) (14030.92048 230.16256) (14008.29604 230.16256) (13978.12930 241.32636)))
("SF_SOLAR" 0 ((13985.67161 7929.86425) (13985.67161 7914.78133)))
("SF_PLANTING" 0 ((13985.67161 3831.07048) (13989.44152 3800.90498)))
("SF_PLANTING" 0 ((13985.67161 3831.07048) (13995.78665 3842.38337) (14004.52489 3880.09050)))
("SF_MASONRY_AND_ARCH" 0 ((13985.67161 2960.03043) (13985.81946 2975.11312) (13993.06493 2997.73756) (13996.98382
3239.06459)))
("SF_MASONRY_AND_ARCH" 0 ((13985.67161 2960.03043) (14023.37817 2960.17817) (14034.69038 2963.80090)))
("SF_MASONRY_AND_ARCH" 0 ((13985.67161 2631.97613) (14000.75373 2635.74661) (14106.33484 2635.74038) (14125.18812
2631.97613)))
("SF_PLANTING" 0 ((14008.29604 516.59219) (13996.98382 512.83337) (13985.67161 516.59219)))
("SF_PLANTING" 0 ((13989.44152 3800.90498) (14019.60826 3782.05170)))
("SF_ARCHITECTURE" 0 ((13993.21267 5720.21109) (14004.52489 5710.10294) (14076.16934 5705.12817) (14091.25147
5720.21109)))
("SF_ARCHITECTURE" 0 ((13993.21267 5720.21109) (14008.29604 5734.08959) (14076.16934 5735.13948) (14083.70351
5731.36855) (14091.25147 5720.21109)))
("SF_MASONRY_AND_ARCH" 0 ((13993.21267 2126.69683) (14008.29604 2127.75317) (14023.37817 2138.00905)))
("SF_PLANTING" 0 ((14038.46154 3235.29412) (13996.98382 3239.06459)))
("SF_SOLAR" 0 ((14000.75373 7993.96674) (14008.29604 7982.65452)))
("SF_SOLAR" 0 ((14211.91595 8042.98643) (14155.35486 8039.21561) (14004.52489 8042.98643)))
("SF_ARCHITECTURE" 0 ((14012.06595 5154.59989) (14004.52489 5173.45441)))
("SF_ARCHITECTURE" 0 ((14004.52489 5173.45441) (14072.39819 5198.65147) (14151.58371 5221.41776) (14245.85260
5241.32771)))
("SF_PLANTING" 0 ((14004.52489 3880.09050) (14023.37817 3880.09050)))
("SF_PLANTING" 0 ((14004.52489 972.85068) (14004.52489 942.68382)))
("SF_PLANTING" 0 ((14004.52489 972.85068) (14015.83710 991.70532)))
("SF_PLANTING" 0 ((14004.52489 942.68382) (14042.23269 912.51980)))
("SF_PLANTING" 0 ((14004.52489 373.30317) (14014.78077 369.37805) (14020.81244 350.67873) (14034.69038 335.59672)))
("SF_PLANTING" 0 ((14004.52489 373.30317) (13994.26900 358.22115) (13993.36041 346.90894) (13998.18111 331.82410)
(14008.29604 320.51188)))
("SF_PLANTING" 0 ((14004.52489 373.30317) (14009.35249 418.55204) (14019.75611 437.25826) (14034.69038 444.94627)))
("SF_SOLAR" 0 ((14008.29604 7963.80090) (14008.29604 7952.48869)))
("SF_PLANTING" 0 ((14008.29604 320.51188) (14034.69038 324.28450)))
("SF_PLANTING" 0 ((14008.29604 267.72342) (14015.83710 267.72342) (14019.60826 275.26301)))
("SF_ARCHITECTURE" 0 ((14012.06595 5154.59989) (14038.46154 5158.37104)))
("SF_PLANTING" 0 ((14012.06595 3959.27602) (14027.14932 3959.27602)))
("SF_MASONRY_AND_ARCH" 0 ((14012.06595 2149.32127) (14023.37817 2138.00905)))
("SF_SOLAR" 0 ((14015.83710 8065.61086) (14030.92048 8058.08258) (14049.77376 8061.83348) (14166.66708 8061.84005)
(14185.52036 8058.21742) (14238.31029 8058.07602) (14253.39367 8061.84005)))
("SF_PLANTING" 0 ((14027.14932 3672.69943) (14015.83710 3748.11505)))
("SF_PLANTING" 0 ((14015.83710 3748.11505) (14019.60826 3782.05170)))
("SF_PLANTING" 0 ((14034.69038 991.70532) (14015.83710 991.70532)))
("SF_PLANTING" 0 ((14030.92048 1040.72398) (14013.27002 1025.64197) (14015.83710 991.70532)))
("SF_SOLAR" 0 ((14019.60826 8125.94276) (14027.14932 8122.17195)))
("SF_PLANTING" 0 ((14019.60826 3782.05170) (14042.08360 3793.51176) (14079.79140 3834.84163) (14091.25147 3857.46606)))
("SF_PLANTING" 0 ((14023.37817 3880.09050) (14030.92738 3876.46776) (14076.16934 3876.31934)))
("SF_PLANTING" 0 ((14023.37817 3880.09050) (14030.92048 3898.94378)))
("SF_MASONRY_AND_ARCH" 0 ((14064.85713 2149.32127) (14053.54491 2141.93416) (14023.37817 2138.00905)))
("SF_PLANTING" 0 ((14027.14932 3959.27602) (14032.11776 3940.42274) (14042.23269 3929.26448) (14049.77376 3925.49400)
(14068.62704 3925.33937)))
("SF_PLANTING" 0 ((14027.14932 3959.27602) (14042.23269 3962.88563) (14049.77376 3959.12138) (14059.88880 3947.96380)
(14068.62704 3925.33937)))
("SF_PLANTING" 0 ((14027.14932 3672.69943) (14034.69038 3668.92952)))
("SF_SOLAR" 0 ((14030.92048 7982.65452) (14030.92048 7993.96674)))
("SF_SOLAR" 0 ((14030.92048 7960.03020) (14030.92048 7952.48869)))
("SF_PLANTING" 0 ((14030.92048 1048.26640) (14030.92048 1040.72398)))
("SF_PLANTING" 0 ((14034.69038 991.70532) (14042.07805 1006.78733) (14042.07805 1025.64197) (14030.92048 1040.72398)))
("SF_SOLAR" 0 ((14057.31482 8163.65000) (14034.69038 8171.19163)))
("SF_SOLAR" 0 ((14034.69038 8095.77670) (14068.62704 8099.54740) (14177.97930 8095.78326) (14234.54038 8103.16369)
(14253.39367 8099.70204) (14279.78925 8103.31833)))
("SF_PLANTING" 0 ((14064.85713 3642.53394) (14042.38744 3651.13167) (14034.69038 3668.92952)))
("SF_PLANTING" 0 ((14061.08597 3684.01165) (14034.69038 3668.92952)))
("SF_PLANTING" 0 ((14042.23269 3604.82681) (14034.69038 3612.36776)))
("SF_MASONRY_AND_ARCH" 0 ((14034.69038 2963.80090) (14053.54491 2956.40690) (14076.16244 2956.40690) (14083.71041
2960.03043)))
("SF_MASONRY_AND_ARCH" 0 ((14038.46154 3235.29412) (14034.69038 2963.80090)))
("SF_PLANTING" 0 ((14034.69038 991.70532) (14061.08597 984.16290)))
("SF_PLANTING" 0 ((14034.69038 444.94627) (14042.08495 422.32183) (14046.00260 343.13631)))
("SF_PLANTING" 0 ((14034.69038 444.94627) (14042.38054 460.03111) (14064.85713 482.65554)))
("SF_PLANTING" 0 ((14034.69038 324.28450) (14034.69038 335.59672)))
("SF_PLANTING" 0 ((14034.69038 335.59672) (14046.00260 343.13631)))
("SF_PLANTING" 0 ((14117.64706 256.41120) (14102.56369 270.43688) (14079.93925 282.95385) (14034.69038 324.28450)))
("SF_PLANTING" 0 ((14038.46154 3235.29412) (14057.31482 3239.06459) (14079.93235 3238.91686) (14087.48156 3235.29412)))
("SF_SOLAR" 0 ((14057.31482 8163.65000) (14056.11753 8144.79638) (14024.42760 8103.31833) (13912.97771 7926.09355)
(13895.16697 7904.66686) (13880.09050 7899.85294) (13865.15622 7904.52534) (13857.76301 7918.55204) (13869.83462
7944.94717) (13912.97771 8005.27896) (13945.39118 8061.84005) (13969.53190 8092.00611) (13986.72805 8125.94276)
(14029.72195 8182.50385) (14042.23269 8208.89887)))
("SF_SOLAR" 0 ((14042.23269 8208.89887) (14057.31482 8212.66968)))
("SF_MASONRY_AND_ARCH" 0 ((14064.85713 2149.32127) (14042.23269 2168.17523)))
("SF_PLANTING" 0 ((14061.08597 1116.13971) (14042.23269 1089.74265)))
("SF_PLANTING" 0 ((14042.23269 912.51980) (14061.08597 912.51980)))
("SF_PLANTING" 0 ((14087.48156 345.02262) (14046.00260 343.13631)))
("SF_PLANTING" 0 ((14091.25147 3993.21267) (14072.40509 4001.80419) (14049.77376 4023.37817)))
("SF_PLANTING" 0 ((14049.77376 256.41120) (14049.77376 237.55656)))
("SF_PLANTING" 0 ((14117.64706 256.41120) (14091.25147 233.94005) (14057.32172 233.93382) (14049.77376 237.55656)))
("SF_SOLAR" 0 ((14053.54491 8084.46448) (14053.54491 8076.92308)))
("SF_SOLAR" 0 ((14053.54491 8024.13281) (14053.54491 8031.67421)))
("SF_SOLAR" 0 ((14053.54491 7960.03020) (14053.54491 7952.48869)))
("SF_ARCHITECTURE" 0 ((14249.62251 5222.47319) (14230.76923 5212.21143) (14170.43699 5199.69480) (14155.35486
5192.46233) (14125.18812 5188.38258) (14079.93925 5170.88088) (14053.54491 5165.91210)))
("SF_SOLAR" 0 ((14057.31482 8163.65000) (14087.48710 8204.97353) (14106.33484 8210.57036) (14562.59468 8208.90543)
(14581.44796 8212.66312) (14698.34129 8212.66312) (14713.42342 8209.04695) (14766.21459 8208.90543) (14785.06787
8212.66312) (14898.19005 8212.66312) (14913.27342 8209.04695) (14966.06335 8208.75079) (14984.91663 8201.65373)
(15018.85328 8211.47206) (15033.93665 8208.91199) (15052.78993 8212.66312) (15203.61991 8212.66312) (15230.01697
8208.89887) (15271.49321 8209.04695) (15286.57805 8212.65656) (15301.65724 8209.04695) (15358.21833 8208.90543)
(15377.07579 8212.66301) (15411.01244 8208.90543) (15437.40385 8212.66968) (15471.34050 8208.90543) (15539.21380
8212.66968) (15569.38348 8208.90543) (15708.89706 8208.90543) (15739.06674 8212.66312) (15757.91855 8208.90543)
(15840.87670 8208.89887)))
("SF_PLANTING" 0 ((14061.08597 3684.01165) (14076.16934 3684.01165)))
("SF_PLANTING" 0 ((14196.83258 3748.11505) (14181.89830 3752.03993) (14144.04265 3792.30724) (14125.18812 3800.75034)
(14106.33484 3795.93654) (14073.45452 3759.42726) (14062.14231 3736.80283) (14057.46946 3710.40724) (14061.08597
3684.01165)))
("SF_PLANTING" 0 ((14061.08597 984.16290) (14061.08597 912.51980)))
("SF_PLANTING" 0 ((14061.08597 984.16290) (14079.93235 989.12376) (14087.48156 995.47511)))
("SF_PLANTING" 0 ((14095.02262 912.51980) (14061.08597 912.51980)))
("SF_SOLAR" 0 ((14064.85713 8141.02557) (14302.41369 8141.01900) (14313.72590 8137.25498)))
("SF_MASONRY_AND_ARCH" 0 ((14098.79378 2160.63348) (14091.24457 2154.28971) (14064.85713 2149.32127)))
("SF_PLANTING" 0 ((14076.16934 3925.33937) (14068.62704 3925.33937)))
("SF_MASONRY_AND_ARCH" 0 ((14159.12477 1410.25735) (14147.96029 1406.33145) (14133.78688 1387.63292) (14086.42523
1308.44740) (14072.39819 1293.36256)))
("SF_SOLAR" 0 ((14076.16934 8171.19163) (14091.25147 8163.65011) (14332.57919 8163.65011)))
("SF_SOLAR" 0 ((14079.93925 8133.48416) (14076.16934 8114.63054)))
("SF_SOLAR" 0 ((14076.16934 7960.03020) (14076.16934 7952.48869)))
("SF_PLANTING" 0 ((14076.16934 3925.33937) (14076.16934 3876.31934)))
("SF_PLANTING" 0 ((14106.33484 3929.11052) (14076.16934 3925.33937)))
("SF_PLANTING" 0 ((14076.16934 3876.31934) (14091.25147 3857.46606)))
("SF_PLANTING" 0 ((14076.16934 3684.01165) (14081.14333 3661.38790) (14091.25147 3652.32930) (14106.33484 3654.90283)
(14121.41821 3665.15837)))
("SF_PLANTING" 0 ((14076.16934 3684.01165) (14098.78688 3695.47229) (14114.02500 3717.94830) (14128.95928 3730.15600)
(14144.03575 3731.82715) (14151.58371 3721.71946)))
("SF_MASONRY_AND_ARCH" 0 ((14098.79378 2160.63348) (14076.16934 2179.48744)))
("SF_PLANTING" 0 ((14076.16934 1014.32975) (14077.37353 1006.78111) (14087.48156 995.47511)))
("SF_SOLAR" 0 ((14079.93925 8024.13281) (14087.48156 8031.67421)))
("SF_PLANTING" 0 ((14079.93925 4204.37364) (14086.28993 4208.29943) (14133.78688 4287.33032) (14158.07523 4310.10283)
(14220.51335 4411.61663) (14229.71290 4419.45419) (14283.55916 4498.49129)))
("SF_MASONRY_AND_ARCH" 0 ((14110.10600 2960.03043) (14083.71041 2960.03043)))
("SF_MASONRY_AND_ARCH" 0 ((14087.48156 3235.29412) (14083.71731 3186.27477) (14083.71041 2960.03043)))
("SF_PLANTING" 0 ((14087.48156 3235.29412) (14117.64706 3235.29412)))
("SF_PLANTING" 0 ((14087.48156 995.47511) (14102.56369 995.47511)))
("SF_PLANTING" 0 ((14091.25147 328.05430) (14087.48156 331.82410) (14087.48156 345.02262)))
("SF_PLANTING" 0 ((14128.95928 426.09446) (14113.87590 425.03733) (14098.94163 417.49570) (14084.61900 395.92760)
(14078.27523 380.84559) (14080.99559 358.21697) (14087.48156 345.02262)))
("SF_PLANTING" 0 ((14113.87590 354.44853) (14087.48156 345.02262)))
("SF_ARCHITECTURE" 0 ((14374.05690 5720.21109) (14091.25147 5720.21109)))
("SF_PLANTING" 0 ((14110.10600 4019.60826) (14091.25147 4064.85713)))
("SF_PLANTING" 0 ((14091.25147 3993.21267) (14096.22681 3951.74118) (14106.33484 3944.19265)))
("SF_PLANTING" 0 ((14091.25147 3993.21267) (14110.10600 4019.60826)))
("SF_PLANTING" 0 ((14128.95928 3861.23722) (14091.25147 3857.46606)))
("SF_SOLAR" 0 ((14098.79378 8220.21109) (14095.02262 8227.75271)))
("SF_PLANTING" 0 ((14095.02262 912.51980) (14102.57059 905.13201) (14144.04265 904.97738)))
("SF_PLANTING" 0 ((14095.02262 912.51980) (14106.18020 931.37161) (14106.33484 991.70532)))
("SF_SOLAR" 0 ((14098.79378 8080.69389) (14098.79378 8073.15226)))
("SF_SOLAR" 0 ((14098.79378 7993.96674) (14098.79378 7982.65452)))
("SF_SOLAR" 0 ((14098.79378 7963.80090) (14098.79378 7948.71799)))
("SF_MASONRY_AND_ARCH" 0 ((14140.27149 2171.94570) (14128.95928 2164.55860) (14098.79378 2160.63348)))
("SF_PLANTING" 0 ((14102.56369 1025.64197) (14102.56369 995.47511)))
("SF_PLANTING" 0 ((14106.33484 991.70532) (14102.56369 995.47511)))
("SF_PLANTING" 0 ((14106.33484 991.70532) (14102.56369 991.70532) (14102.56369 995.47511)))
("SF_PLANTING" 0 ((14106.33484 3929.11052) (14106.33484 3944.19265)))
("SF_PLANTING" 0 ((14110.10600 4019.60826) (14125.18258 4024.43484) (14144.04265 4041.02138) (14154.15079 4034.68416)
(14155.20713 4004.52489) (14150.52738 3993.21267) (14106.33484 3944.19265)))
("SF_PLANTING" 0 ((14106.33484 3929.11052) (14125.18812 3917.64989) (14142.15645 3900.82998)))
("SF_PLANTING" 0 ((14140.27149 976.62048) (14117.64706 990.50045) (14106.33484 991.70532)))
("SF_MASONRY_AND_ARCH" 0 ((14151.58371 2960.03043) (14132.73043 2956.25916) (14110.10600 2960.03043)))
("SF_MASONRY_AND_ARCH" 0 ((14117.64706 3235.29412) (14113.88281 3197.58699) (14113.86900 2975.11312) (14110.10600
2960.03043)))
("SF_MASONRY_AND_ARCH" 0 ((14140.27149 2171.94570) (14121.41821 2189.59548) (14110.10600 2190.79966)))
("SF_PLANTING" 0 ((14110.10600 380.84559) (14113.87590 354.44853)))
("SF_PLANTING" 0 ((14140.27149 354.44853) (14113.87590 354.44853)))
("SF_PLANTING" 0 ((14117.64706 3235.29412) (14132.73043 3239.06459) (14151.58371 3235.29412)))
("SF_PLANTING" 0 ((14128.95928 260.18100) (14117.64706 256.41120)))
("SF_SOLAR" 0 ((14125.18812 8114.63054) (14121.41821 8133.48416)))
("SF_SOLAR" 0 ((14121.41821 8069.38167) (14121.41821 8080.69389)))
("SF_SOLAR" 0 ((14121.41821 8031.67421) (14121.41821 8024.13281)))
("SF_SOLAR" 0 ((14121.41821 7918.55204) (14121.41821 7926.09355)))
("SF_SOLAR" 0 ((14136.50034 7843.13722) (14121.41821 7843.13722)))
("SF_PLANTING" 0 ((14140.27149 3684.01165) (14125.34276 3676.32251) (14121.41821 3665.15837)))
("SF_PLANTING" 0 ((14121.41821 3665.15837) (14136.49344 3666.35600) (14144.04265 3672.69943)))
("SF_PLANTING" 0 ((14121.41821 275.26301) (14121.41821 282.80543)))
("SF_PLANTING" 0 ((14121.41821 275.26301) (14113.87590 279.03563) (14121.41821 282.80543)))
("SF_PLANTING" 0 ((14121.41821 282.80543) (14133.92771 309.19966) (14147.81256 324.28450)))
("SF_PLANTING" 0 ((14128.95928 260.18100) (14121.41821 267.72342) (14121.41821 275.26301)))
("SF_PLANTING" 0 ((14200.60373 3808.44604) (14159.12477 3820.81493) (14133.78688 3846.15385) (14128.95928 3861.23722)))
("SF_PLANTING" 0 ((14142.15645 3900.82998) (14130.00871 3876.31934) (14128.95928 3861.23722)))
("SF_PLANTING" 0 ((14128.95928 426.09446) (14130.16346 403.47002) (14140.27149 393.36120) (14151.58371 392.15781)))
("SF_PLANTING" 0 ((14128.95928 426.09446) (14136.50724 436.20181) (14159.12477 437.40667)))
("SF_PLANTING" 0 ((14144.04265 260.18100) (14128.95928 260.18100)))
("SF_MASONRY_AND_ARCH" 0 ((14132.73043 2575.41505) (14140.27149 2575.41505)))
("SF_MASONRY_AND_ARCH" 0 ((14189.29152 1568.62839) (14179.03575 1561.07907) (14150.53428 1512.06731) (14132.73043
1489.44287)))
("SF_SOLAR" 0 ((14788.83903 7895.92760) (14762.29570 7854.45611) (14739.81900 7843.28529) (14494.72138 7846.91459)
(14472.09695 7850.67851) (14404.22364 7843.14378) (14370.28699 7854.30136) (14151.58371 7850.68529) (14136.50034
7858.22025)))
("SF_SOLAR" 0 ((14140.27149 7982.65452) (14144.04265 7993.96674)))
("SF_ARCHITECTURE" 0 ((14140.27149 4400.45249) (14150.52738 4411.76471) (14194.11086 4487.02511) (14200.60373
4490.95023)))
("SF_PLANTING" 0 ((14140.27149 3684.01165) (14144.04265 3672.69943)))
("SF_PLANTING" 0 ((14151.58371 3721.71946) (14140.27149 3684.01165)))
("SF_MASONRY_AND_ARCH" 0 ((14140.27149 2575.41505) (14154.15079 2552.79061) (14159.12477 2526.39491)))
("SF_MASONRY_AND_ARCH" 0 ((14151.58371 2590.49774) (14140.27149 2575.41505)))
("SF_MASONRY_AND_ARCH" 0 ((14140.27149 2171.94570) (14181.74921 2179.48744)))
("SF_PLANTING" 0 ((14151.58371 950.22624) (14140.27149 976.62048)))
("SF_PLANTING" 0 ((14166.66708 995.47511) (14140.27149 976.62048)))
("SF_PLANTING" 0 ((14140.27149 354.44853) (14147.81256 324.28450)))
("SF_PLANTING" 0 ((14151.58371 392.15781) (14140.27149 354.44853)))
("SF_PLANTING" 0 ((14142.15645 3900.82998) (14159.12477 3885.06550) (14200.60373 3883.86165)))
("SF_PLANTING" 0 ((14155.35486 3917.79830) (14142.15645 3900.82998)))
("SF_SOLAR" 0 ((14144.04265 8031.67421) (14144.04265 8020.36199)))
("SF_SOLAR" 0 ((14144.04265 7960.03020) (14144.04265 7952.48869)))
("SF_PLANTING" 0 ((14144.04265 3672.69943) (14159.12477 3668.92952)))
("SF_MASONRY_AND_ARCH" 0 ((14181.74921 2179.48744) (14162.89593 2200.90769) (14144.04265 2202.11188)))
("SF_PLANTING" 0 ((14144.04265 904.97738) (14177.97930 904.97738)))
("SF_PLANTING" 0 ((14144.04265 904.97738) (14141.46867 927.60181) (14145.23993 942.67896) (14151.58371 950.22624)))
("SF_PLANTING" 0 ((14144.04265 260.18100) (14151.73145 245.09898) (14166.66708 233.94005) (14238.31029 230.16256)
(14260.93473 241.32636)))
("SF_PLANTING" 0 ((14144.04265 260.18100) (14155.35486 271.49321)))
("SF_PLANTING" 0 ((14159.12477 324.28450) (14147.81256 324.28450)))
("SF_SOLAR" 0 ((14151.58371 7911.01052) (14192.00498 7956.25939) (14196.83258 7971.34231)))
("SF_PLANTING" 0 ((14151.58371 3721.71946) (14159.12477 3721.71946)))
("SF_PLANTING" 0 ((14151.58371 3235.29412) (14170.43699 3235.29412)))
("SF_MASONRY_AND_ARCH" 0 ((14161.01097 3146.68201) (14144.19740 3167.42081) (14147.80011 3197.58699) (14144.19740
3216.44016) (14151.58371 3235.29412)))
("SF_MASONRY_AND_ARCH" 0 ((14151.58371 2960.03043) (14174.20814 2960.03043)))
("SF_MASONRY_AND_ARCH" 0 ((14155.35486 3137.25464) (14147.96719 3129.70679) (14144.04955 3088.23529) (14151.58371
2960.03043)))
("SF_MASONRY_AND_ARCH" 0 ((14151.58371 2590.49774) (14151.58371 2598.03948)))
("SF_MASONRY_AND_ARCH" 0 ((14151.58371 2590.49774) (14159.13167 2584.15396) (14174.20814 2582.95600)))
("SF_PLANTING" 0 ((14159.12477 950.22624) (14151.58371 950.22624)))
("SF_PLANTING" 0 ((14151.58371 392.15781) (14159.12477 414.78224)))
("SF_PLANTING" 0 ((14155.35486 3917.79830) (14189.29152 3917.79830)))
("SF_PLANTING" 0 ((14155.35486 3917.79830) (14160.32330 3944.19265) (14174.21505 3961.84898) (14189.29152 3966.81708)))
("SF_MASONRY_AND_ARCH" 0 ((14155.35486 3137.25464) (14162.89593 3137.25464)))
("SF_MASONRY_AND_ARCH" 0 ((14161.01097 3146.68201) (14155.35486 3144.79638) (14155.35486 3137.25464)))
("SF_MASONRY_AND_ARCH" 0 ((14170.43699 2658.37104) (14155.35486 2665.91256)))
("SF_PLANTING" 0 ((14166.66708 995.47511) (14161.69876 1014.17443) (14155.35486 1018.09955)))
("SF_PLANTING" 0 ((14177.97930 452.48869) (14155.35486 478.88292)))
("SF_PLANTING" 0 ((14155.35486 271.49321) (14159.12477 324.28450)))
("SF_PLANTING" 0 ((14181.74921 279.03563) (14170.43699 272.54955) (14155.35486 271.49321)))
("SF_SOLAR" 0 ((14189.29152 8114.63054) (14166.67398 8114.48247) (14159.12477 8110.85973)))
("SF_MASONRY_AND_ARCH" 0 ((14166.66708 2526.39491) (14159.12477 2526.39491)))
("SF_MASONRY_AND_ARCH" 0 ((14166.66708 1406.48473) (14159.12477 1410.25735)))
("SF_MASONRY_AND_ARCH" 0 ((14159.12477 1410.25735) (14166.66708 1429.10916)))
("SF_PLANTING" 0 ((14159.12477 950.22624) (14165.46991 942.67896) (14167.87127 927.60871) (14177.97930 920.05939)))
("SF_PLANTING" 0 ((14159.12477 950.22624) (14181.74921 972.85068)))
("SF_PLANTING" 0 ((14159.12477 437.40667) (14159.12477 414.78224)))
("SF_PLANTING" 0 ((14177.97930 452.48869) (14159.12477 437.40667)))
("SF_PLANTING" 0 ((14159.12477 414.78224) (14185.52036 403.47002)))
("SF_PLANTING" 0 ((14189.29152 331.82410) (14159.12477 324.28450)))
("SF_MASONRY_AND_ARCH" 0 ((14161.01097 3146.68201) (14162.89593 3137.25464)))
("SF_MASONRY_AND_ARCH" 0 ((14161.01097 3146.68201) (14170.28224 3163.65034) (14174.06041 3193.81572) (14174.06041
3223.98190) (14170.43699 3235.29412)))
("SF_MASONRY_AND_ARCH" 0 ((14174.20814 2960.03043) (14177.97240 2986.42534) (14174.35588 3001.50803) (14174.06041
3076.92308) (14170.58473 3088.23529) (14170.28224 3129.70679) (14162.89593 3137.25464)))
("SF_SOLAR" 0 ((14166.66708 8069.38167) (14166.66708 8080.69389)))
("SF_SOLAR" 0 ((14170.43699 8031.67421) (14166.66708 8020.36199)))
("SF_PLANTING" 0 ((14166.66708 3601.05554) (14177.97930 3616.13903)))
("SF_MASONRY_AND_ARCH" 0 ((14166.66708 2526.39491) (14166.66708 2511.31222)))
("SF_MASONRY_AND_ARCH" 0 ((14347.66256 2526.39491) (14219.45701 2526.40113) (14204.37364 2530.01154) (14166.66708
2526.39491)))
("SF_MASONRY_AND_ARCH" 0 ((14166.66708 2484.91731) (14166.66708 2477.37557)))
("SF_MASONRY_AND_ARCH" 0 ((14166.66708 1429.10916) (14170.59163 1444.18643) (14185.52036 1451.73360)))
("SF_MASONRY_AND_ARCH" 0 ((14166.66708 1429.10916) (14181.59446 1436.65848) (14185.52036 1451.73360)))
("SF_PLANTING" 0 ((14166.66708 995.47511) (14181.74921 972.85068)))
("SF_PLANTING" 0 ((14215.68586 3235.29412) (14200.60373 3239.06459) (14177.98620 3238.91686) (14170.43699 3235.29412)))
("SF_MASONRY_AND_ARCH" 0 ((14170.43699 2658.37104) (14171.64106 2639.67172) (14181.74921 2635.74661)))
("SF_MASONRY_AND_ARCH" 0 ((14170.43699 2658.37104) (14177.98620 2665.91256) (14302.41369 2665.91256) (14321.26697
2665.91256) (14351.43247 2665.91256)))
("SF_PLANTING" 0 ((14196.83258 3748.11505) (14206.94061 3736.80215) (14216.87749 3706.63609) (14229.71290 3684.01165)
(14230.61459 3653.85238) (14226.84333 3647.50894) (14215.68586 3646.45294) (14193.06143 3651.13167) (14174.20814
3661.38722)))
("SF_MASONRY_AND_ARCH" 0 ((14211.91595 2960.03043) (14196.83258 2956.25916) (14174.20814 2960.03043)))
("SF_PLANTING" 0 ((14177.97930 904.97738) (14177.97930 920.05939)))
("SF_PLANTING" 0 ((14196.83258 957.76867) (14188.08744 931.37161) (14177.97930 920.05939)))
("SF_PLANTING" 0 ((14294.87138 904.97738) (14276.01810 901.20758) (14193.06143 901.35464) (14177.97930 904.97738)))
("SF_PLANTING" 0 ((14177.97930 452.48869) (14189.29152 452.48869)))
("SF_MASONRY_AND_ARCH" 0 ((14181.74921 2179.48744) (14226.99118 2188.22636) (14234.54038 2194.57014)))
("SF_PLANTING" 0 ((14181.74921 972.85068) (14196.83258 972.85068)))
("SF_MASONRY_AND_ARCH" 0 ((14291.10147 1610.10464) (14209.20113 1493.21267) (14185.52036 1451.73360)))
("SF_PLANTING" 0 ((14193.06143 350.67873) (14185.52036 403.47002)))
("SF_PLANTING" 0 ((14189.29152 414.78224) (14185.52036 403.47002)))
("SF_SOLAR" 0 ((14189.29152 8122.17195) (14189.29152 8133.48416)))
("SF_SOLAR" 0 ((14189.29152 8076.92308) (14189.29152 8069.38167)))
("SF_PLANTING" 0 ((14189.29152 3917.79830) (14196.67794 3944.19265) (14189.29152 3966.81708)))
("SF_PLANTING" 0 ((14249.62251 4004.52489) (14238.31029 4008.14106) (14226.99808 4003.46821) (14204.37364 3985.66471)
(14189.29152 3966.81708)))
("SF_PLANTING" 0 ((14189.29152 3917.79830) (14200.60373 3910.25600)))
("SF_PLANTING" 0 ((14193.06143 3691.55396) (14189.29152 3714.17839)))
("SF_MASONRY_AND_ARCH" 0 ((14189.29152 1568.62839) (14200.60373 1553.54355)))
("SF_MASONRY_AND_ARCH" 0 ((14189.29152 1568.62839) (14190.49570 1579.93303) (14200.60373 1587.48020)))
("SF_PLANTING" 0 ((14189.29152 527.90441) (14189.29152 520.36199)))
("SF_PLANTING" 0 ((14215.68586 520.36199) (14189.29152 520.36199)))
("SF_PLANTING" 0 ((14193.06143 486.42534) (14189.29152 520.36199)))
("SF_PLANTING" 0 ((14211.91595 429.86425) (14196.83948 441.18269) (14189.29152 452.48869)))
("SF_PLANTING" 0 ((14193.06143 486.42534) (14189.29152 452.48869)))
("SF_PLANTING" 0 ((14189.29152 331.82410) (14193.05452 320.51188) (14189.29152 305.42986)))
("SF_PLANTING" 0 ((14193.06143 350.67873) (14189.29152 331.82410)))
("SF_ARCHITECTURE" 0 ((14468.32579 5599.54751) (14411.76471 5588.23529) (14385.36912 5595.77636) (14238.31029
5595.77014) (14223.22817 5592.30238) (14193.06143 5599.54751)))
("SF_ARCHITECTURE" 0 ((14468.32579 5599.54751) (14453.24242 5618.40124) (14215.68586 5618.24638) (14193.06143
5599.54751)))
("SF_PLANTING" 0 ((14193.06143 3691.55396) (14193.06143 3684.01165)))
("SF_PLANTING" 0 ((14193.06143 3691.55396) (14200.60373 3695.32387)))
("SF_PLANTING" 0 ((14193.06143 486.42534) (14215.67896 481.45068) (14223.22817 471.34333)))
("SF_PLANTING" 0 ((14223.22817 350.67873) (14193.06143 350.67873)))
("SF_SOLAR" 0 ((14223.22817 8005.27896) (14222.02410 7997.73088) (14207.99706 7978.89050) (14196.83258 7971.34231)))
("SF_SOLAR" 0 ((14343.89140 7941.17647) (14321.26697 7937.41233) (14219.45701 7937.25113) (14211.92149 7933.48032)
(14196.83258 7914.78133)))
("SF_PLANTING" 0 ((14196.83258 3748.11505) (14204.37364 3782.05170)))
("SF_MASONRY_AND_ARCH" 0 ((14351.43247 2575.41505) (14343.88450 2579.03778) (14287.33032 2579.33326) (14276.01810
2582.80826) (14208.14480 2583.11063) (14196.83258 2590.49774)))
("SF_PLANTING" 0 ((14196.83258 972.85068) (14196.83258 957.76867)))
("SF_PLANTING" 0 ((14196.83258 972.85068) (14233.33631 1010.55713) (14235.74457 1033.18156) (14249.62251 1046.91312)
(14268.47704 1043.29038) (14289.90294 1018.09955) (14291.10147 1006.78733)))
("SF_PLANTING" 0 ((14208.14480 953.99604) (14196.83258 957.76867)))
("SF_ARCHITECTURE" 0 ((14211.91595 4483.40916) (14200.60373 4490.95023)))
("SF_ARCHITECTURE" 0 ((14200.60373 4490.95023) (14208.29253 4504.97692) (14223.22817 4509.80351)))
("SF_PLANTING" 0 ((14200.60373 3895.17387) (14200.60373 3910.25600)))
("SF_PLANTING" 0 ((14234.54038 3951.73495) (14200.60373 3910.25600)))
("SF_PLANTING" 0 ((14200.60373 3895.17387) (14249.62251 3895.17387)))
("SF_PLANTING" 0 ((14200.60373 3895.17387) (14200.60373 3883.86165)))
("SF_PLANTING" 0 ((14219.45701 3846.15385) (14209.34197 3857.46606) (14200.60373 3883.86165)))
("SF_PLANTING" 0 ((14200.60373 3808.44604) (14204.37364 3782.05170)))
("SF_PLANTING" 0 ((14219.45701 3846.15385) (14200.60373 3808.44604)))
("SF_MASONRY_AND_ARCH" 0 ((14211.91595 1583.71041) (14200.60373 1587.48020)))
("SF_MASONRY_AND_ARCH" 0 ((14200.60373 1587.48020) (14201.80792 1595.02885) (14211.91595 1606.33484)))
("SF_PLANTING" 0 ((14351.43247 3782.05170) (14336.35034 3785.52568) (14283.55916 3770.73948) (14245.85260 3770.88733)
(14204.37364 3782.05170)))
("SF_ARCHITECTURE" 0 ((14211.91595 4483.40916) (14208.14480 4472.09695)))
("SF_MASONRY_AND_ARCH" 0 ((14208.14480 1572.39819) (14211.91595 1583.71041)))
("SF_SOLAR" 0 ((14211.91595 8133.48416) (14211.91595 8118.40113)))
("SF_SOLAR" 0 ((14211.91595 8069.38167) (14211.91595 8084.46448)))
("SF_SOLAR" 0 ((14211.91595 8024.13281) (14208.14480 8027.90339) (14211.91595 8035.44502)))
("SF_ARCHITECTURE" 0 ((14211.91595 4483.40916) (14218.26527 4487.33405) (14223.22817 4509.80351)))
("SF_MASONRY_AND_ARCH" 0 ((14211.91595 2960.03043) (14238.31029 2960.03043)))
("SF_MASONRY_AND_ARCH" 0 ((14211.91595 2960.03043) (14212.06380 3031.67421) (14216.73529 3042.83179) (14223.22817
3046.75690)))
("SF_MASONRY_AND_ARCH" 0 ((14219.45701 1602.56505) (14211.91595 1606.33484)))
("SF_MASONRY_AND_ARCH" 0 ((14223.22817 1625.18948) (14213.12014 1613.88213) (14211.91595 1606.33484)))
("SF_MASONRY_AND_ARCH" 0 ((14211.91595 1583.71041) (14218.25984 1591.25769) (14219.45701 1602.56505)))
("SF_PLANTING" 0 ((14215.68586 3235.29412) (14234.54038 3235.29412)))
("SF_MASONRY_AND_ARCH" 0 ((14223.22817 3084.46482) (14212.07070 3099.54751) (14211.92285 3216.44016) (14215.68586
3235.29412)))
("SF_SOLAR" 0 ((14358.97477 7967.57172) (14347.66256 7971.33575) (14242.08145 7971.18767) (14230.91697 7963.79434)
(14219.45701 7944.94717)))
("SF_PLANTING" 0 ((14219.45701 3846.15385) (14257.16482 3842.53111) (14283.55916 3856.41629) (14302.41369 3861.23722)))
("SF_MASONRY_AND_ARCH" 0 ((14219.45701 2209.65283) (14234.54038 2194.57014)))
("SF_MASONRY_AND_ARCH" 0 ((14219.45701 1602.56505) (14229.56505 1610.11222) (14230.76923 1625.18948)))
("SF_ARCHITECTURE" 0 ((14340.12025 4690.79898) (14289.90430 4611.62036) (14277.06753 4600.15339) (14243.13088
4551.28247) (14223.22817 4509.80351)))
("SF_MASONRY_AND_ARCH" 0 ((14223.22817 3084.46482) (14223.22817 3046.75690)))
("SF_MASONRY_AND_ARCH" 0 ((14223.22817 3084.46482) (14234.38575 3099.54751) (14234.54038 3235.29412)))
("SF_MASONRY_AND_ARCH" 0 ((14223.22817 3046.75690) (14234.38575 3039.20905) (14238.15554 3031.67421) (14241.93371
2967.57828) (14238.31029 2960.03043)))
("SF_MASONRY_AND_ARCH" 0 ((14309.95475 2631.97613) (14223.22817 2631.97613)))
("SF_MASONRY_AND_ARCH" 0 ((14223.22817 1625.18948) (14230.76923 1625.18948)))
("SF_MASONRY_AND_ARCH" 0 ((14223.22817 1625.18948) (14227.15271 1636.49412) (14242.08145 1644.04129)))
("SF_PLANTING" 0 ((14223.22817 411.00962) (14223.22817 403.47002) (14230.76923 395.92760)))
("SF_PLANTING" 0 ((14242.08145 297.88744) (14240.88428 316.74208) (14223.22817 350.67873)))
("SF_PLANTING" 0 ((14223.22817 350.67873) (14226.99808 358.22115)))
("SF_PLANTING" 0 ((14245.85260 938.91403) (14226.99808 938.91403)))
("SF_PLANTING" 0 ((14279.78925 316.74208) (14253.39367 350.53032) (14242.08145 357.16403) (14226.99808 358.22115)))
("SF_PLANTING" 0 ((14230.76923 395.92760) (14226.99808 358.22115)))
("SF_PLANTING" 0 ((14230.76923 3966.81708) (14234.54038 3951.73495)))
("SF_MASONRY_AND_ARCH" 0 ((14230.76923 1625.18948) (14240.87726 1632.73665) (14242.08145 1644.04129)))
("SF_PLANTING" 0 ((14230.76923 395.92760) (14249.62251 399.69740)))
("SF_PLANTING" 0 ((14242.08145 297.88744) (14230.76923 275.26301)))
("SF_SOLAR" 0 ((14234.54038 8069.38167) (14234.54038 8084.46448)))
("SF_SOLAR" 0 ((14234.54038 7918.55204) (14238.31029 7926.09355)))
("SF_PLANTING" 0 ((14257.16482 3910.25600) (14252.18948 3947.80916) (14234.54038 3951.73495)))
("SF_PLANTING" 0 ((14234.54038 3235.29412) (14249.62251 3239.06459) (14283.55916 3235.29412)))
("SF_MASONRY_AND_ARCH" 0 ((14475.86686 2228.50679) (14347.66256 2216.13824) (14317.49581 2206.03009) (14234.54038
2194.57014)))
("SF_SOLAR" 0 ((14238.31029 8009.04977) (14245.85260 7997.73756)))
("SF_MASONRY_AND_ARCH" 0 ((14283.55916 2960.03043) (14260.93473 2956.25916) (14238.31029 2960.03043)))
("SF_MASONRY_AND_ARCH" 0 ((14245.85260 1662.89593) (14242.08145 1644.04129)))
("SF_PLANTING" 0 ((14242.08145 297.88744) (14268.47704 294.11765)))
("SF_SOLAR" 0 ((14245.85260 7978.88394) (14247.05679 7986.43201) (14283.55916 8039.21561)))
("SF_ARCHITECTURE" 0 ((14249.62251 5222.47319) (14245.85260 5241.32771)))
("SF_ARCHITECTURE" 0 ((14302.41369 5252.63993) (14268.47704 5248.72070) (14245.85260 5241.32771)))
("SF_PLANTING" 0 ((14249.62251 3895.17387) (14245.85260 3883.86165)))
("SF_MASONRY_AND_ARCH" 0 ((14257.16482 1685.52036) (14245.85260 1662.89593)))
("SF_MASONRY_AND_ARCH" 0 ((14264.70588 1685.52036) (14260.77998 1670.44321) (14245.85260 1662.89593)))
("SF_PLANTING" 0 ((14245.85260 938.91403) (14246.00045 957.76867) (14250.67885 968.92557) (14264.69898 972.69604)
(14272.24695 965.30826)))
("SF_PLANTING" 0 ((14272.24695 946.45645) (14245.85260 938.91403)))
("SF_ARCHITECTURE" 0 ((14306.18360 5233.78541) (14298.49480 5227.44197) (14279.78925 5222.62161) (14249.62251
5222.47319)))
("SF_PLANTING" 0 ((14249.62251 3895.17387) (14257.16482 3910.25600)))
("SF_PLANTING" 0 ((14272.24695 395.92760) (14249.62251 399.69740)))
("SF_PLANTING" 0 ((14260.93473 452.48869) (14249.77715 426.09446) (14249.62251 399.69740)))
("SF_SOLAR" 0 ((14257.16482 8114.63054) (14257.16482 8129.71335)))
("SF_SOLAR" 0 ((14260.93473 8027.90339) (14257.16482 8035.44502)))
("SF_SOLAR" 0 ((14257.16482 7956.25939) (14257.16482 7948.71799)))
("SF_SOLAR" 0 ((14257.16482 7926.09355) (14257.16482 7918.55204)))
("SF_PLANTING" 0 ((14285.44536 3912.14219) (14257.16482 3910.25600)))
("SF_MASONRY_AND_ARCH" 0 ((14264.70588 1685.52036) (14257.16482 1685.52036)))
("SF_MASONRY_AND_ARCH" 0 ((14260.93473 1696.83258) (14257.16482 1685.52036)))
("SF_SOLAR" 0 ((14260.93473 8061.84005) (14292.15102 8106.93428) (14298.64253 8110.85973)))
("SF_PLANTING" 0 ((14260.93473 241.32636) (14272.24695 233.94005) (14306.18360 233.94005) (14325.03812 245.09898)))
("SF_PLANTING" 0 ((14260.93473 241.32636) (14268.47704 275.26301)))
("SF_PLANTING" 0 ((14264.70588 3989.44152) (14276.01810 3974.35939)))
("SF_MASONRY_AND_ARCH" 0 ((14264.70588 1685.52036) (14274.82093 1693.06765) (14351.43247 1817.49717)))
("SF_SOLAR" 0 ((14268.47704 8054.29864) (14283.55916 8039.21561)))
("SF_PLANTING" 0 ((14268.47704 294.11765) (14268.47704 275.26301)))
("SF_PLANTING" 0 ((14279.78925 316.74208) (14268.47704 294.11765)))
("SF_PLANTING" 0 ((14302.41369 275.26301) (14268.47704 275.26301)))
("SF_SOLAR" 0 ((14385.36912 8005.27896) (14374.05690 8012.66595) (14302.41369 8012.66595) (14272.24695 7997.73756)))
("SF_PLANTING" 0 ((14302.41369 965.30826) (14272.24695 965.30826)))
("SF_PLANTING" 0 ((14272.24695 946.45645) (14272.24695 965.30826)))
("SF_PLANTING" 0 ((14272.24695 946.45645) (14291.10147 927.60181)))
("SF_PLANTING" 0 ((14283.55916 373.30317) (14272.24695 395.92760)))
("SF_PLANTING" 0 ((14325.03812 358.22115) (14336.18880 377.07296) (14335.14627 384.61538) (14325.03812 394.87127)
(14309.95475 399.69253) (14272.24695 395.92760)))
("SF_SOLAR" 0 ((14279.78925 7948.71799) (14279.78925 7960.03020)))
("SF_SOLAR" 0 ((14279.78925 7918.55204) (14279.78925 7929.86425)))
("SF_PLANTING" 0 ((14438.16029 516.59219) (14291.10147 516.58529) (14279.78925 512.81957)))
("SF_PLANTING" 0 ((14279.78925 316.74208) (14304.29864 316.74208)))
("SF_SOLAR" 0 ((14287.33032 8061.84005) (14283.55916 8073.15226)))
("SF_SOLAR" 0 ((14283.55916 8039.21561) (14301.35735 8061.84005) (14329.85747 8110.85973) (14361.54050 8148.56052)
(14362.74468 8156.10860)))
("SF_MASONRY_AND_ARCH" 0 ((14283.55916 2960.03043) (14279.78925 2978.88360) (14283.55226 3009.04977) (14283.55226
3148.56686) (14279.78925 3178.73303) (14283.55916 3235.29412)))
("SF_PLANTING" 0 ((14313.72590 3239.06459) (14291.10837 3238.91686) (14283.55916 3235.29412)))
("SF_MASONRY_AND_ARCH" 0 ((14283.55916 2960.03043) (14313.72590 2960.03043)))
("SF_PLANTING" 0 ((14302.41369 3861.23722) (14295.01912 3880.09050) (14293.81222 3898.94751) (14285.44536 3912.14219)))
("SF_PLANTING" 0 ((14374.05690 3966.81708) (14332.57919 3966.66923) (14302.41369 3958.07839) (14288.38665 3940.42274)
(14283.78145 3921.50124) (14285.44536 3912.14219)))
("SF_PLANTING" 0 ((14285.44536 3912.14219) (14309.95475 3914.02715)))
("SF_PLANTING" 0 ((14298.64253 1070.89084) (14294.87138 1070.89084) (14291.10147 1063.34842)))
("SF_PLANTING" 0 ((14294.87138 904.97738) (14291.10147 927.60181)))
("SF_PLANTING" 0 ((14302.41369 965.30826) (14301.35735 942.68382) (14291.10147 927.60181)))
("SF_PLANTING" 0 ((14336.35034 904.97738) (14294.87138 904.97738)))
("SF_SOLAR" 0 ((14306.18360 8103.31833) (14298.64253 8110.85973)))
("SF_SOLAR" 0 ((14313.72590 8137.25498) (14299.84672 8118.40781) (14298.64253 8110.85973)))
("SF_PLANTING" 0 ((14298.64253 1070.89084) (14336.35034 1058.52149) (14351.43247 1040.72398)))
("SF_PLANTING" 0 ((14298.64253 1070.89084) (14302.41369 1078.43043)))
("SF_SOLAR" 0 ((14302.41369 7997.73756) (14317.49581 7997.73756)))
("SF_SOLAR" 0 ((14302.41369 7948.71799) (14302.41369 7960.03020)))
("SF_SOLAR" 0 ((14302.41369 7929.86425) (14302.41369 7918.55204)))
("SF_ARCHITECTURE" 0 ((14306.18360 5233.78541) (14302.41369 5252.63993)))
("SF_ARCHITECTURE" 0 ((14385.36912 5260.18100) (14302.41369 5252.63993)))
("SF_PLANTING" 0 ((14302.41369 3861.23722) (14317.49581 3860.03247) (14336.35034 3843.58744) (14370.28699 3833.78563)
(14404.22364 3815.98835)))
("SF_PLANTING" 0 ((14321.26697 969.08088) (14302.41369 965.30826)))
("SF_PLANTING" 0 ((14302.41369 275.26301) (14325.03812 260.18100)))
("SF_PLANTING" 0 ((14302.41369 275.26301) (14304.29864 316.74208)))
("SF_PLANTING" 0 ((14340.12025 316.74208) (14304.29864 316.74208)))
("SF_PLANTING" 0 ((14325.03812 358.22115) (14317.49581 357.01629) (14309.05995 346.90894) (14304.29864 316.74208)))
("SF_ARCHITECTURE" 0 ((14306.18360 5233.78541) (14351.43247 5233.93382) (14370.28009 5238.76075) (14385.36912
5252.63993)))
("SF_SOLAR" 0 ((14611.61346 8061.84005) (14596.53133 8058.08258) (14577.67681 8061.83348) (14453.24242 8061.83348)
(14438.16029 8058.36550) (14423.07692 8061.82692) (14309.95475 8054.29864)))
("SF_PLANTING" 0 ((14313.72590 1184.01301) (14307.23303 1180.08710) (14302.56154 1168.92817) (14309.95475 1134.99152)))
("SF_SOLAR" 0 ((14313.72590 8137.25498) (14332.57919 8163.65011)))
("SF_PLANTING" 0 ((14313.72590 3540.72398) (14332.43145 3559.57794) (14339.96550 3574.66063) (14336.19570 3585.82511)
(14317.49581 3597.28507)))
("SF_PLANTING" 0 ((14313.72590 3239.06459) (14351.43247 3239.06459)))
("SF_MASONRY_AND_ARCH" 0 ((14313.72590 3239.06459) (14309.95475 3208.89921) (14313.71900 3171.19129) (14313.57817
3095.77704) (14309.95475 3076.92308) (14313.71900 3054.29864) (14313.72590 2960.03043)))
("SF_MASONRY_AND_ARCH" 0 ((14347.66256 2960.03043) (14313.72590 2960.03043)))
("SF_PLANTING" 0 ((14336.35034 1018.09955) (14321.41471 1022.92647) (14313.72590 1033.18156)))
("SF_PLANTING" 0 ((14321.26697 969.08088) (14321.26697 980.39310)))
("SF_PLANTING" 0 ((14321.26697 969.08088) (14336.35034 970.13654) (14347.66256 976.62048)))
("SF_SOLAR" 0 ((14325.03812 8035.44502) (14325.03812 8027.90339)))
("SF_SOLAR" 0 ((14325.03812 7982.65452) (14325.03812 7990.19615)))
("SF_SOLAR" 0 ((14325.03812 7952.48869) (14325.03812 7963.80090)))
("SF_SOLAR" 0 ((14328.80803 7926.09355) (14325.03812 7914.78133)))
("SF_PLANTING" 0 ((14340.12025 316.74208) (14338.91606 346.76052) (14325.03812 358.22115)))
("SF_PLANTING" 0 ((14325.03812 245.09898) (14325.03812 260.18100)))
("SF_PLANTING" 0 ((14347.66256 305.42986) (14341.16968 294.11765) (14338.91606 275.26301) (14325.03812 260.18100)))
("SF_PLANTING" 0 ((14362.74468 245.09898) (14325.03812 245.09898)))
("SF_SOLAR" 0 ((14328.80803 8125.94276) (14328.80803 8137.25498)))
("SF_SOLAR" 0 ((14664.40464 8163.65011) (14653.09242 8163.65011) (14332.57919 8163.65011)))
("SF_SOLAR" 0 ((14336.35034 8095.77670) (14362.74468 8103.17025) (14426.84808 8103.31833)))
("SF_PLANTING" 0 ((14336.35034 904.97738) (14347.66256 901.21244) (14445.70136 901.21244) (14464.55464 908.74717)))
("SF_PLANTING" 0 ((14336.35034 904.97738) (14347.81041 927.59559) (14376.77172 950.37398) (14385.36912 969.08088)))
("SF_SOLAR" 0 ((14366.51584 8042.98643) (14340.12025 8046.75724)))
("SF_PLANTING" 0 ((14340.12025 316.74208) (14347.66256 305.42986)))
("SF_SOLAR" 0 ((14347.66256 8080.69389) (14343.89140 8069.38167)))
("SF_SOLAR" 0 ((14343.89140 7941.17647) (14358.97477 7937.40577) (14404.22364 7937.55385) (14457.01357 7944.94061)
(14517.33891 7944.79910) (14524.88688 7941.17647)))
("SF_SOLAR" 0 ((14358.97477 7967.57172) (14345.09559 7948.72455) (14343.89140 7941.17647)))
("SF_PLANTING" 0 ((14351.43247 3506.78733) (14343.89140 3514.32907)))
("SF_PLANTING" 0 ((14366.51584 1078.43043) (14348.85984 1101.05486) (14343.89140 1127.45192)))
("SF_SOLAR" 0 ((14347.66256 7993.96674) (14347.66256 7982.65452)))
("SF_MASONRY_AND_ARCH" 0 ((14347.66256 2960.03043) (14385.36912 2956.40769) (14404.22364 2963.80090)))
("SF_MASONRY_AND_ARCH" 0 ((14347.66256 2960.03043) (14351.43247 3239.06459)))
("SF_MASONRY_AND_ARCH" 0 ((14347.66256 2526.39491) (14347.66256 2549.01934)))
("SF_MASONRY_AND_ARCH" 0 ((14611.61346 2518.85396) (14596.53133 2522.61821) (14377.82805 2522.63066) (14347.66256
2526.39491)))
("SF_PLANTING" 0 ((14381.59921 286.57523) (14370.28699 296.69027) (14347.66256 305.42986)))
("SF_PLANTING" 0 ((14351.43247 3774.50939) (14351.43247 3782.05170)))
("SF_PLANTING" 0 ((14351.43247 3782.05170) (14374.05690 3792.31346) (14389.13337 3794.56776) (14404.22364 3815.98835)))
("SF_PLANTING" 0 ((14351.43247 3774.50939) (14377.82805 3751.87873) (14392.91143 3733.03167)))
("SF_PLANTING" 0 ((14381.59921 3661.38722) (14328.80803 3661.23937) (14302.41369 3643.73846) (14287.33722 3642.68857)
(14281.00034 3646.45905) (14284.75633 3668.92952) (14301.35735 3699.09502) (14303.61097 3710.40724) (14341.17658
3766.96210) (14351.43247 3774.50939)))
("SF_PLANTING" 0 ((14351.43247 3612.36776) (14381.59921 3627.45057)))
("SF_PLANTING" 0 ((14400.45249 3231.52364) (14392.90452 3237.86742) (14374.05690 3242.68812) (14351.43247 3239.06459)))
("SF_MASONRY_AND_ARCH" 0 ((14913.27342 2665.91256) (14894.41889 2665.91256) (14845.40011 2665.91256) (14807.69231
2665.91256) (14630.46799 2665.91256) (14607.84355 2665.91256) (14551.28247 2665.91256) (14532.42794 2665.91256)
(14445.70136 2665.91256) (14419.30577 2665.91256) (14370.28699 2665.91256) (14351.43247 2665.91256)))
("SF_MASONRY_AND_ARCH" 0 ((14913.27342 2631.97590) (14894.41889 2631.97590) (14841.62896 2631.97590) (14830.31674
2631.97590) (14819.00452 2631.97590) (14754.90238 2631.97590) (14739.81900 2631.97590) (14724.73563 2631.97590)
(14362.74468 2628.35950) (14352.63654 2635.75351) (14351.43247 2665.91256)))
("SF_PLANTING" 0 ((14415.53586 3865.00713) (14404.22364 3866.20532) (14374.05690 3887.77998) (14355.20362 3914.02715)))
("SF_SOLAR" 0 ((14358.97477 7967.57172) (14407.99355 7975.11312)))
("SF_PLANTING" 0 ((14392.91143 3733.03167) (14388.08394 3721.87410) (14358.97477 3699.09502)))
("SF_PLANTING" 0 ((14362.74468 245.09898) (14377.82805 233.78586) (14430.61799 233.78586)))
("SF_PLANTING" 0 ((14362.74468 245.09898) (14376.62387 263.95079) (14381.59921 286.57523)))
("SF_SOLAR" 0 ((14366.51584 8190.04525) (14370.28699 8197.58665)))
("SF_PLANTING" 0 ((14366.51584 1010.55713) (14367.72002 1003.00995) (14384.16493 984.16290) (14385.36912 969.08088)))
("SF_SOLAR" 0 ((14460.78473 8137.25498) (14453.23552 8140.87760) (14370.28699 8141.02557)))
("SF_SOLAR" 0 ((14385.36912 8005.27896) (14375.11324 7993.96674) (14370.28699 7978.88394)))
("SF_PLANTING" 0 ((14374.05690 3966.81708) (14370.28699 3955.50486)))
("SF_SOLAR" 0 ((14374.05690 8114.63054) (14374.05690 8122.17195)))
("SF_ARCHITECTURE" 0 ((14374.05690 5720.21109) (14389.14027 5705.12817) (14438.16029 5705.12817) (14449.47251
5712.66968)))
("SF_ARCHITECTURE" 0 ((14374.05690 5720.21109) (14392.91143 5735.13948) (14438.16029 5735.13948) (14449.47251
5727.75271)))
("SF_PLANTING" 0 ((14374.05690 3966.81708) (14381.59921 3966.81708)))
("SF_PLANTING" 0 ((14377.82805 3601.05554) (14381.59921 3627.45057)))
("SF_SOLAR" 0 ((14381.59921 8042.98643) (14389.14027 8042.98643)))
("SF_SOLAR" 0 ((14389.14027 7960.03020) (14381.59921 7948.71799)))
("SF_PLANTING" 0 ((14381.59921 3966.81708) (14396.67579 3965.61324) (14411.77161 3948.11844) (14423.07692 3944.19265)))
("SF_PLANTING" 0 ((14381.59921 3966.81708) (14382.79649 3981.89423) (14389.14027 3989.44152)))
("SF_PLANTING" 0 ((14381.59921 3661.38722) (14381.59921 3627.45057)))
("SF_PLANTING" 0 ((14381.59921 3661.38722) (14386.42545 3676.47059) (14404.22364 3691.55396)))
("SF_PLANTING" 0 ((14381.59921 286.57523) (14404.22364 304.37353) (14419.30577 309.19966)))
("SF_SOLAR" 0 ((14385.36912 8005.27896) (14449.47251 8012.67251) (14573.90690 8012.82059)))
("SF_ARCHITECTURE" 0 ((14385.36912 5260.18100) (14385.36912 5252.63993)))
("SF_ARCHITECTURE" 0 ((14502.26244 5263.95215) (14490.95023 5271.33857) (14472.09695 5271.48699) (14457.01357
5267.87048) (14400.45249 5267.56810) (14385.36912 5260.18100)))
("SF_ARCHITECTURE" 0 ((14502.26244 5263.95215) (14490.95023 5250.07330) (14464.55464 5245.24604) (14396.68133
5245.25260) (14385.36912 5252.63993)))
("SF_PLANTING" 0 ((14385.36912 969.08088) (14407.99355 961.68620) (14426.84808 961.53846)))
("SF_PLANTING" 0 ((14449.47251 414.78224) (14434.38914 414.92930) (14400.45249 425.79061) (14393.05928 422.16855)
(14382.79649 407.23982) (14370.43484 369.53337) (14371.49118 343.29163) (14377.82805 339.66889) (14385.36912
343.13631)))
("SF_SOLAR" 0 ((14392.91143 8084.46448) (14389.14027 8069.38167)))
("SF_SOLAR" 0 ((14404.22364 8050.52783) (14389.14027 8020.36199)))
("SF_PLANTING" 0 ((14392.91143 3733.03167) (14415.53586 3733.03167)))
("SF_MASONRY_AND_ARCH" 0 ((14400.45249 3231.52364) (14400.45939 3012.82025) (14404.22364 2963.80090)))
("SF_PLANTING" 0 ((14458.89853 3237.17975) (14419.30577 3238.91618) (14400.45249 3231.52364)))
("SF_PLANTING" 0 ((14453.24242 343.13631) (14434.38224 365.59989) (14400.45249 350.67873)))
("SF_PLANTING" 0 ((14434.38914 3819.75826) (14426.84118 3816.13620) (14404.22364 3815.98835)))
("SF_PLANTING" 0 ((14404.22364 3691.55396) (14415.53586 3676.47059)))
("SF_PLANTING" 0 ((14419.30577 3717.94830) (14404.22364 3691.55396)))
("SF_MASONRY_AND_ARCH" 0 ((14404.22364 2963.80090) (14419.30577 2960.03043) (14445.69446 2960.17817) (14453.24242
2963.80090)))
("SF_SOLAR" 0 ((14415.53586 7997.73756) (14407.99355 7975.11312)))
("SF_SOLAR" 0 ((14407.99355 7975.11312) (14460.78473 7975.26109) (14479.63801 7978.88371) (14517.34581 7975.26120)
(14547.51131 7982.65452)))
("SF_SOLAR" 0 ((14415.53586 8133.48416) (14411.76471 8114.63054)))
("SF_SOLAR" 0 ((14411.76471 7929.86425) (14411.76471 7922.32274)))
("SF_SOLAR" 0 ((14415.53586 8069.38167) (14438.16029 8098.34321) (14460.78473 8096.98100) (14472.09695 8103.46640)
(14498.33654 8129.86143) (14502.26244 8141.02557)))
("SF_PLANTING" 0 ((14434.38914 3831.07048) (14424.13326 3842.38337) (14415.53586 3865.00713)))
("SF_PLANTING" 0 ((14430.61799 3891.40271) (14415.53586 3865.00713)))
("SF_PLANTING" 0 ((14415.53586 3733.03167) (14415.53586 3721.71946) (14419.30577 3717.94830)))
("SF_PLANTING" 0 ((14441.93020 3751.88495) (14430.61799 3750.68111) (14415.53586 3733.03167)))
("SF_PLANTING" 0 ((14415.53586 3657.61731) (14415.53586 3676.47059)))
("SF_PLANTING" 0 ((14487.17907 3657.61731) (14496.23767 3680.24174) (14475.86686 3698.03835) (14457.01357 3697.89050)
(14441.93020 3685.20984) (14415.53586 3676.47059)))
("SF_PLANTING" 0 ((14415.53586 3627.45057) (14420.50984 3604.83303) (14430.61799 3597.28507)))
("SF_PLANTING" 0 ((14415.53586 3499.24559) (14415.53586 3521.87002)))
("SF_PLANTING" 0 ((14430.61799 3717.94830) (14419.30577 3717.94830)))
("SF_PLANTING" 0 ((14430.61799 233.78586) (14434.23450 271.49321) (14419.30577 309.19966)))
("SF_PLANTING" 0 ((14453.24242 328.05430) (14426.85498 319.45622) (14419.30577 309.19966)))
("SF_PLANTING" 0 ((14430.61799 3891.40271) (14423.22466 3910.25600) (14423.07692 3944.19265)))
("SF_PLANTING" 0 ((14423.07692 3944.19265) (14445.70136 3959.27602)))
("SF_SOLAR" 0 ((14426.84808 8020.36199) (14441.93020 8050.52783)))
("SF_SOLAR" 0 ((14426.84808 7956.25939) (14430.61799 7963.80090)))
("SF_PLANTING" 0 ((14464.55464 908.74717) (14426.84808 961.53846)))
("SF_PLANTING" 0 ((14438.16029 980.39310) (14426.84808 961.53846)))
("SF_PLANTING" 0 ((14430.61799 4061.08597) (14426.85498 4046.00260) (14430.61799 4030.92048)))
("SF_PLANTING" 0 ((14430.61799 3891.40271) (14460.78473 3887.63156)))
("SF_PLANTING" 0 ((14430.61799 3597.28507) (14445.55362 3585.82511) (14468.32579 3552.03620)))
("SF_PLANTING" 0 ((14430.61799 3597.28507) (14449.47251 3611.45294) (14460.78473 3612.36776)))
("SF_PLANTING" 0 ((14430.61799 1074.66063) (14438.16029 1070.89084)))
("SF_PLANTING" 0 ((14483.40916 241.32636) (14457.01357 233.78586) (14430.61799 233.78586)))
("SF_PLANTING" 0 ((14434.38914 3819.75826) (14434.38914 3831.07048)))
("SF_PLANTING" 0 ((14434.38914 3831.07048) (14460.78473 3857.46606)))
("SF_PLANTING" 0 ((14434.38914 3819.75826) (14445.70136 3800.90498)))
("SF_PLANTING" 0 ((14438.16029 1123.67930) (14434.38914 1108.59729)))
("SF_SOLAR" 0 ((14438.16029 8110.85973) (14460.78473 8137.25498)))
("SF_SOLAR" 0 ((14438.16029 7933.63495) (14438.16029 7918.55204)))
("SF_PLANTING" 0 ((14438.16029 1070.89084) (14441.93020 1044.49378)))
("SF_PLANTING" 0 ((14438.16029 1070.89084) (14453.24242 1081.00441) (14472.09695 1085.97285)))
("SF_PLANTING" 0 ((14438.16029 980.39310) (14445.70136 980.39310)))
("SF_PLANTING" 0 ((14438.16029 980.39310) (14420.49740 1006.78733) (14417.64174 1018.09955) (14423.22466 1029.41176)
(14441.93020 1044.49378)))
("SF_PLANTING" 0 ((14441.93020 3751.88495) (14498.49129 3733.17975) (14524.88688 3733.03167)))
("SF_PLANTING" 0 ((14441.93020 3751.88495) (14442.07794 3793.35701) (14445.70136 3800.90498)))
("SF_PLANTING" 0 ((14475.86686 1021.86934) (14453.24242 1043.29038) (14441.93020 1044.49378)))
("SF_PLANTING" 0 ((14468.32579 3914.02715) (14457.90837 3944.19265) (14445.70136 3959.27602)))
("SF_PLANTING" 0 ((14468.32579 4012.06595) (14467.26946 4000.75373) (14450.52896 3974.35939) (14445.70136 3959.27602)))
("SF_PLANTING" 0 ((14445.70136 3800.90498) (14479.63801 3800.75690) (14513.57466 3793.36391)))
("SF_PLANTING" 0 ((14445.70136 980.39310) (14464.40679 965.30339) (14487.17907 935.14423)))
("SF_PLANTING" 0 ((14475.86686 1021.86934) (14445.70136 980.39310)))
("SF_SOLAR" 0 ((14506.03360 8039.21561) (14494.72138 8042.83846) (14449.47251 8042.98643)))
("SF_ARCHITECTURE" 0 ((14449.47251 5727.75271) (14449.47251 5712.66968)))
("SF_ARCHITECTURE" 0 ((14449.47251 5727.75271) (14464.55464 5735.13948) (14487.17907 5735.13948) (14494.71448
5731.36855) (14502.26244 5720.21109)))
("SF_ARCHITECTURE" 0 ((14502.26244 5720.21109) (14487.17907 5705.12817) (14449.47251 5712.66968)))
("SF_MASONRY_AND_ARCH" 0 ((14464.55464 3065.61086) (14449.47251 3065.61086)))
("SF_MASONRY_AND_ARCH" 0 ((14449.47251 3065.61086) (14449.32477 3012.82025) (14445.99683 3001.50803) (14453.24242
2963.80090)))
("SF_MASONRY_AND_ARCH" 0 ((14449.47251 3065.61086) (14449.47941 3163.65034) (14453.24242 3178.73303)))
("SF_PLANTING" 0 ((14449.47251 444.94627) (14449.47251 414.78224)))
("SF_PLANTING" 0 ((14449.47251 414.78224) (14468.32579 399.69740) (14490.95023 373.30317)))
("SF_SOLAR" 0 ((14464.55464 8088.23529) (14453.24242 8073.15226)))
("SF_MASONRY_AND_ARCH" 0 ((14464.55464 3178.73303) (14453.24242 3178.73303)))
("SF_PLANTING" 0 ((14453.24242 3178.73303) (14449.62036 3190.04525) (14449.62036 3220.21143) (14458.89853 3237.17975)))
("SF_MASONRY_AND_ARCH" 0 ((14464.55464 2963.80090) (14453.24242 2963.80090)))
("SF_PLANTING" 0 ((14453.24242 343.13631) (14453.24242 328.05430)))
("SF_PLANTING" 0 ((14490.95023 358.22115) (14468.32579 353.24514) (14453.24242 343.13631)))
("SF_PLANTING" 0 ((14453.24242 328.05430) (14463.49819 320.50701) (14468.32579 301.66007)))
("SF_PLANTING" 0 ((14464.55464 3178.73303) (14471.80011 3197.58699) (14467.05396 3227.82002) (14458.89853 3237.17975)))
("SF_PLANTING" 0 ((14517.34581 3235.29412) (14494.72138 3242.82964) (14475.86686 3242.68733) (14458.89853 3237.17975)))
("SF_SOLAR" 0 ((14460.78473 8137.25498) (14475.86686 8144.50023) (14502.26244 8141.02557)))
("SF_SOLAR" 0 ((14464.55464 8031.67421) (14460.78473 8024.13281)))
("SF_SOLAR" 0 ((14460.78473 7956.25939) (14460.78473 7967.57172)))
("SF_SOLAR" 0 ((14460.78473 7918.55204) (14460.78473 7933.63495)))
("SF_PLANTING" 0 ((14460.78473 3887.63156) (14460.78473 3857.46606)))
("SF_PLANTING" 0 ((14468.32579 3906.48609) (14460.78473 3887.63156)))
("SF_PLANTING" 0 ((14490.95023 3853.69491) (14460.78473 3857.46606)))
("SF_PLANTING" 0 ((14487.17907 3657.61731) (14464.55464 3653.84615)))
("SF_MASONRY_AND_ARCH" 0 ((14464.55464 3178.73303) (14468.32579 3163.65034) (14468.17805 3076.92308) (14464.55464
3065.61086)))
("SF_MASONRY_AND_ARCH" 0 ((14464.55464 3065.61086) (14468.32579 3050.52817) (14468.17805 2975.11312) (14464.55464
2963.80090)))
("SF_MASONRY_AND_ARCH" 0 ((14517.34581 2963.80090) (14498.49129 2960.03043) (14472.10385 2960.17817) (14464.55464
2963.80090)))
("SF_PLANTING" 0 ((14464.55464 908.74717) (14483.40916 908.74717)))
("SF_ARCHITECTURE" 0 ((14558.82353 5599.54751) (14468.32579 5599.54751)))
("SF_PLANTING" 0 ((14468.32579 3914.02715) (14475.86686 3914.02715)))
("SF_PLANTING" 0 ((14468.32579 3914.02715) (14468.32579 3906.48609)))
("SF_PLANTING" 0 ((14468.32579 3906.48609) (14472.09695 3906.48609) (14475.86686 3914.02715)))
("SF_PLANTING" 0 ((14506.03360 294.11765) (14468.32579 301.66007)))
("SF_PLANTING" 0 ((14483.40916 252.63857) (14473.30113 260.18790) (14470.89977 279.03563) (14464.71618 290.34785)
(14468.32579 301.66007)))
("SF_PLANTING" 0 ((14506.03360 3925.33937) (14475.86686 3914.02715)))
("SF_MASONRY_AND_ARCH" 0 ((14517.34581 2202.11188) (14475.86686 2228.50679)))
("SF_MASONRY_AND_ARCH" 0 ((14517.34581 2202.11188) (14528.65758 2213.42410) (14528.65758 2236.04163) (14520.96097
2242.38541) (14494.72138 2242.53314) (14475.86686 2228.50679)))
("SF_PLANTING" 0 ((14475.86686 1021.86934) (14500.37749 1019.98586)))
("SF_ARCHITECTURE" 0 ((14513.57466 5064.10215) (14479.63801 5094.26889)))
("SF_ARCHITECTURE" 0 ((14513.57466 5064.10215) (14524.73224 5079.18552) (14523.83054 5094.26821) (14517.19672
5104.37636) (14494.72138 5105.42613) (14479.63801 5094.26889)))
("SF_SOLAR" 0 ((14622.92568 8103.31833) (14600.30124 8099.56063) (14585.21912 8103.17025) (14517.34581 8103.31821)
(14483.40916 8099.54751)))
("SF_SOLAR" 0 ((14483.40916 8001.50837) (14483.40916 7986.42534)))
("SF_SOLAR" 0 ((14483.40916 7963.80090) (14483.40916 7956.25939)))
("SF_SOLAR" 0 ((14483.40916 7922.32274) (14483.40916 7929.86425)))
("SF_SOLAR" 0 ((14509.80351 7911.01052) (14483.40916 7911.01052)))
("SF_PLANTING" 0 ((14528.65803 901.20758) (14494.72138 901.36086) (14483.40916 908.74717)))
("SF_PLANTING" 0 ((14483.40916 908.74717) (14487.17907 935.14423)))
("SF_PLANTING" 0 ((14483.40916 252.63857) (14483.40916 241.32636)))
("SF_PLANTING" 0 ((14483.40916 252.63857) (14506.03360 275.26301)))
("SF_PLANTING" 0 ((14483.40916 241.32636) (14506.03360 233.78586) (14517.34581 233.78586) (14532.42794 233.78586)
(14543.74016 245.09898)))
("SF_SOLAR" 0 ((14494.72138 7888.38609) (14494.56674 7869.53247) (14487.17907 7858.22025)))
("SF_PLANTING" 0 ((14487.17907 3657.61731) (14502.26244 3616.13903)))
("SF_PLANTING" 0 ((14498.49129 938.91403) (14487.17907 935.14423)))
("SF_SOLAR" 0 ((14490.95023 8073.15226) (14506.03360 8084.46448)))
("SF_PLANTING" 0 ((14490.95023 3853.69491) (14494.72138 3834.84163)))
("SF_PLANTING" 0 ((14490.95023 3853.69491) (14494.87613 3860.18744) (14517.33891 3872.69729) (14524.88688 3883.86165)))
("SF_PLANTING" 0 ((14490.95023 475.11312) (14498.49129 478.88292)))
("SF_PLANTING" 0 ((14490.95023 358.22115) (14490.95023 373.30317)))
("SF_PLANTING" 0 ((14490.95023 373.30317) (14508.74706 395.92760) (14511.00758 422.31697) (14528.65803 432.43066)
(14543.59231 422.32183) (14551.13473 407.23982) (14550.22613 392.15781) (14539.97025 377.07296)))
("SF_PLANTING" 0 ((14490.95023 358.22115) (14509.80351 350.67873)))
("SF_SOLAR" 0 ((14498.49129 8193.81606) (14494.72138 8174.96222)))
("SF_SOLAR" 0 ((14494.72138 7888.38609) (14509.80351 7902.26482) (14539.96335 7903.61719) (14547.51131 7907.23982)))
("SF_PLANTING" 0 ((14526.77183 937.02771) (14506.04050 935.29129) (14498.49129 938.91403)))
("SF_PLANTING" 0 ((14498.49129 938.91403) (14509.80351 980.39310)))
("SF_PLANTING" 0 ((14498.49129 501.50735) (14498.49129 478.88292)))
("SF_PLANTING" 0 ((14506.03360 456.25848) (14507.54989 463.80781) (14498.49129 478.88292)))
("SF_PLANTING" 0 ((14500.37749 1019.98586) (14499.54491 1006.79084) (14509.80351 980.39310)))
("SF_PLANTING" 0 ((14500.37749 1019.98586) (14503.46663 1052.03620) (14517.34581 1063.34842)))
("SF_PLANTING" 0 ((14521.11572 1021.86934) (14500.37749 1019.98586)))
("SF_SOLAR" 0 ((14502.26244 8141.02557) (14638.00905 8141.01900) (14649.32127 8137.25498)))
("SF_ARCHITECTURE" 0 ((15064.10215 5720.21109) (14502.26244 5720.21109)))
("SF_ARCHITECTURE" 0 ((14607.84355 5263.95215) (14502.26244 5263.95215)))
("SF_PLANTING" 0 ((14509.80351 3616.13903) (14502.26244 3616.13903)))
("SF_PLANTING" 0 ((14502.26244 3616.13903) (14492.14197 3604.82681) (14487.17907 3582.20238) (14492.14197 3559.57794)
(14502.26244 3544.49446)))
("SF_SOLAR" 0 ((14506.03360 8039.21561) (14551.28247 8039.21561)))
("SF_SOLAR" 0 ((14506.03360 8039.21561) (14506.03360 8024.13281)))
("SF_SOLAR" 0 ((14506.03360 7986.42534) (14506.03360 8001.50837)))
("SF_SOLAR" 0 ((14506.03360 7956.25939) (14506.03360 7963.80090)))
("SF_PLANTING" 0 ((14524.88688 3921.56821) (14506.03360 3925.33937)))
("SF_PLANTING" 0 ((14506.03360 3925.33937) (14508.90860 3940.41584) (14517.34581 3947.96380)))
("SF_PLANTING" 0 ((14506.03360 294.11765) (14513.57466 294.11765)))
("SF_PLANTING" 0 ((14506.03360 294.11765) (14506.03360 275.26301)))
("SF_PLANTING" 0 ((14506.03360 275.26301) (14513.58156 268.92059) (14539.97025 263.95079)))
("SF_PLANTING" 0 ((14528.65803 980.39310) (14509.80351 980.39310)))
("SF_PLANTING" 0 ((14513.57466 294.11765) (14509.80351 350.67873)))
("SF_PLANTING" 0 ((14539.97025 365.76075) (14509.80351 350.67873)))
("SF_PLANTING" 0 ((14513.57466 5064.10215) (14513.58156 3993.21267) (14517.34581 3947.96380)))
("SF_PLANTING" 0 ((14513.57466 3793.36391) (14518.40226 3759.42726) (14528.65803 3744.34389)))
("SF_PLANTING" 0 ((14513.57466 3793.36391) (14532.42794 3797.13382)))
("SF_PLANTING" 0 ((14543.74016 294.11765) (14513.57466 294.11765)))
("SF_SOLAR" 0 ((14517.34581 7918.55204) (14524.88688 7941.17647)))
("SF_PLANTING" 0 ((14528.65803 3936.65158) (14524.88688 3944.19265) (14517.34581 3947.96380)))
("SF_MASONRY_AND_ARCH" 0 ((14517.34581 2963.80090) (14517.34581 3235.29412)))
("SF_PLANTING" 0 ((14570.13575 3239.06459) (14536.19910 3242.68733) (14517.34581 3235.29412)))
("SF_MASONRY_AND_ARCH" 0 ((14517.34581 2963.80090) (14539.97025 2956.40690) (14562.58778 2956.40690) (14570.13575
2960.03043)))
("SF_MASONRY_AND_ARCH" 0 ((14517.34581 2202.11188) (14517.34581 1063.34842)))
("SF_PLANTING" 0 ((14528.65758 1048.26640) (14517.34581 1063.34842)))
("SF_PLANTING" 0 ((14521.11572 1021.86934) (14531.37149 1003.01753) (14532.42794 991.70532)))
("SF_PLANTING" 0 ((14521.11572 1021.86934) (14528.65758 1033.18156) (14528.65758 1048.26640)))
("SF_SOLAR" 0 ((14573.90690 8012.82059) (14572.70837 8001.50826) (14550.22613 7967.57172) (14524.88688 7941.17647)))
("SF_PLANTING" 0 ((14524.88688 3883.86165) (14524.88688 3921.56821)))
("SF_PLANTING" 0 ((14528.65803 3936.65158) (14528.65803 3925.33937) (14524.88688 3921.56821)))
("SF_PLANTING" 0 ((14524.88688 3883.86165) (14570.13575 3891.40271)))
("SF_PLANTING" 0 ((14562.59468 3699.09502) (14543.74016 3710.56188) (14524.88688 3733.03167)))
("SF_PLANTING" 0 ((14528.65803 3744.34389) (14524.88688 3733.03167)))
("SF_PLANTING" 0 ((14524.88688 392.15781) (14539.97025 377.07296)))
("SF_PLANTING" 0 ((14526.77183 937.02771) (14528.65803 901.20758)))
("SF_PLANTING" 0 ((14528.65803 980.39310) (14526.77183 937.02771)))
("SF_PLANTING" 0 ((14526.77183 937.02771) (14536.13145 937.64219) (14566.36459 923.83201)))
("SF_PLANTING" 0 ((14570.13575 1048.26640) (14528.65758 1048.26640)))
("SF_SOLAR" 0 ((14528.65803 8182.50385) (14532.42794 8174.96222)))
("SF_SOLAR" 0 ((14528.65803 8118.40113) (14528.65803 8125.94276)))
("SF_PLANTING" 0 ((14570.13575 3947.96380) (14528.65803 3936.65158)))
("SF_PLANTING" 0 ((14690.79898 3751.88495) (14679.48676 3748.26290) (14638.00905 3747.96007) (14622.92568 3740.72771)
(14570.13575 3740.72115) (14543.74016 3747.96663) (14528.65803 3744.34389)))
("SF_PLANTING" 0 ((14528.65803 980.39310) (14532.42794 991.70532)))
("SF_PLANTING" 0 ((14566.36459 908.74717) (14555.05238 901.36086) (14528.65803 901.20758)))
("SF_SOLAR" 0 ((14532.42794 7990.19615) (14536.19910 8001.50837)))
("SF_SOLAR" 0 ((14536.19910 7963.80090) (14532.42794 7971.34231)))
("SF_PLANTING" 0 ((14619.15577 3789.59276) (14532.42794 3797.13382)))
("SF_PLANTING" 0 ((14532.42794 3797.13382) (14543.89480 3831.06425) (14570.13575 3846.15385)))
("SF_PLANTING" 0 ((14532.42794 991.70532) (14566.36459 991.70532)))
("SF_PLANTING" 0 ((14539.97025 365.76075) (14539.97025 377.07296)))
("SF_PLANTING" 0 ((14539.97025 365.76075) (14547.37048 361.83631) (14555.05238 346.90894)))
("SF_PLANTING" 0 ((14539.97025 263.95079) (14543.74016 245.09898)))
("SF_PLANTING" 0 ((14539.97025 263.95079) (14543.59231 271.50011) (14543.74016 294.11765)))
("SF_SOLAR" 0 ((14883.10667 8058.06946) (14874.51618 8039.21561) (14820.05396 7956.25939) (14799.09491 7914.78133)
(14788.83903 7904.67342) (14570.13575 7903.32104) (14555.05238 7898.50057) (14544.94423 7888.38609) (14543.74016
7861.99095)))
("SF_PLANTING" 0 ((14543.74016 294.11765) (14543.88790 320.51188) (14555.05238 346.90894)))
("SF_PLANTING" 0 ((14573.90690 245.09898) (14543.74016 245.09898)))
("SF_SOLAR" 0 ((14558.82353 7941.17647) (14547.51131 7944.94717)))
("SF_SOLAR" 0 ((14551.28247 8133.48416) (14551.28247 8118.40113)))
("SF_SOLAR" 0 ((14551.28247 8024.13281) (14551.28247 8039.21561)))
("SF_SOLAR" 0 ((14581.44796 8042.98643) (14558.83043 8042.83846) (14551.28247 8039.21561)))
("SF_SOLAR" 0 ((14573.90690 7941.17647) (14555.05238 7918.55204)))
("SF_PLANTING" 0 ((14562.59468 346.90894) (14555.05238 346.90894)))
("SF_ARCHITECTURE" 0 ((14558.82353 5599.54751) (14566.37149 5588.23529) (14600.30124 5588.23529) (14611.61346
5599.54751)))
("SF_ARCHITECTURE" 0 ((14558.82353 5599.54751) (14577.67681 5618.40124) (14585.21912 5618.40124) (14596.53133
5618.40124) (14611.61346 5599.54751)))
("SF_PLANTING" 0 ((14630.46799 501.50735) (14562.59468 501.50735)))
("SF_PLANTING" 0 ((14562.59468 346.90894) (14572.85057 331.82410) (14577.52896 312.97229) (14573.90690 245.09898)))
("SF_PLANTING" 0 ((14588.98903 380.84559) (14581.30023 365.76075) (14562.59468 346.90894)))
("SF_SOLAR" 0 ((14566.36459 7963.80090) (14566.36459 7975.11312)))
("SF_PLANTING" 0 ((14566.36459 923.83201) (14570.13575 969.08088) (14566.36459 991.70532)))
("SF_PLANTING" 0 ((14566.36459 991.70532) (14569.98801 999.25249) (14570.13575 1040.72398)))
("SF_PLANTING" 0 ((14566.36459 908.74717) (14566.36459 923.83201)))
("SF_PLANTING" 0 ((14566.36459 908.74717) (14604.07240 908.74717)))
("SF_ARCHITECTURE" 0 ((15260.18100 4015.83710) (15256.41674 4027.14932) (15255.20566 5003.76425) (15226.24434
5021.57466) (15154.59989 5051.73450) (15086.72658 5074.35894) (14943.43891 5112.97410) (14747.36007 5146.91075)
(14570.13575 5158.37104)))
("SF_ARCHITECTURE" 0 ((14570.13575 3947.96380) (14570.12885 4049.77376) (14566.36459 4072.39819) (14566.37149
4981.14672) (14570.13575 5003.77115) (14570.12885 5113.12217) (14566.37149 5135.74661) (14570.13575 5158.37104)))
("SF_PLANTING" 0 ((14570.13575 3947.96380) (14615.38462 3944.19265)))
("SF_PLANTING" 0 ((14570.13575 3947.96380) (14570.13575 3891.40271)))
("SF_PLANTING" 0 ((14570.13575 3891.40271) (14576.62726 3887.47760) (14581.44796 3876.31934)))
("SF_PLANTING" 0 ((14592.76018 3834.84163) (14577.68371 3836.04581) (14570.13575 3846.15385)))
("SF_PLANTING" 0 ((14581.44796 3876.31934) (14570.13575 3846.15385)))
("SF_PLANTING" 0 ((14570.13575 3239.06459) (14607.83665 3238.91686) (14615.38462 3235.29412)))
("SF_MASONRY_AND_ARCH" 0 ((14570.13575 3239.06459) (14570.14265 3156.10860) (14573.90690 3133.48416) (14570.13575
2960.03043)))
("SF_MASONRY_AND_ARCH" 0 ((14570.13575 2960.03043) (14577.68371 2956.40690) (14600.30124 2956.40769) (14619.15577
2963.80090)))
("SF_MASONRY_AND_ARCH" 0 ((14570.13575 2307.69231) (14675.71686 2307.68609) (14724.73563 2303.77410) (14766.21459
2296.52783) (14826.54559 2292.46188) (14954.75113 2269.83744) (15169.68326 2212.36765) (15294.11765 2167.11878)
(15339.36652 2146.60713) (15369.53054 2141.77952)))
("SF_MASONRY_AND_ARCH" 0 ((14570.13575 1048.26640) (14570.13575 2307.69231)))
("SF_PLANTING" 0 ((14570.13575 1048.26640) (14570.13575 1040.72398)))
("SF_PLANTING" 0 ((14604.07240 1040.72398) (14570.13575 1040.72398)))
("SF_SOLAR" 0 ((14573.90690 8012.82059) (14600.30124 8050.52783)))
("SF_SOLAR" 0 ((14573.90690 7941.17647) (14585.21912 7937.41233) (14622.92568 7941.17647) (14758.67229 7937.41233)
(14785.06787 7944.94717)))
("SF_SOLAR" 0 ((14573.90690 7941.17647) (14582.50430 7963.79434) (14592.76018 7971.34231)))
("SF_PLANTING" 0 ((14600.30124 241.32636) (14573.90690 245.09898)))
("SF_SOLAR" 0 ((14577.67681 8069.38167) (14581.44796 8076.92308) (14577.67681 8084.46448)))
("SF_SOLAR" 0 ((14577.67681 7990.19615) (14585.21912 7978.88394)))
("SF_PLANTING" 0 ((14624.81188 3878.20554) (14581.44796 3876.31934)))
("SF_PLANTING" 0 ((14588.98903 380.84559) (14581.44796 407.23982)))
("SF_SOLAR" 0 ((14588.98903 8012.82059) (14596.53133 8001.50837)))
("SF_PLANTING" 0 ((14588.98903 380.84559) (14600.14649 384.77002) (14608.90000 403.47002) (14622.92568 418.55204)))
("SF_SOLAR" 0 ((14592.76018 7971.34231) (14803.92115 7971.33575) (14815.23337 7967.57172)))
("SF_SOLAR" 0 ((14698.34129 8141.02557) (14684.30735 8129.71335) (14663.34830 8092.00611) (14623.98201 8035.44502)
(14592.76018 7971.34231)))
("SF_SOLAR" 0 ((14596.53133 7929.86425) (14596.53133 7914.78133)))
("SF_PLANTING" 0 ((14600.30124 241.32636) (14611.61346 233.78586) (14641.78020 233.78586) (14653.09242 233.78586)))
("SF_PLANTING" 0 ((14600.30124 241.32636) (14626.69683 290.34785)))
("SF_PLANTING" 0 ((14604.07240 1040.72398) (14604.07240 1010.55713)))
("SF_PLANTING" 0 ((14604.07240 1040.72398) (14619.15577 1052.03620)))
("SF_PLANTING" 0 ((14626.69683 1010.55713) (14604.07240 1010.55713)))
("SF_PLANTING" 0 ((14604.07240 908.74717) (14604.22014 972.85068) (14607.83122 987.93269) (14604.07240 1010.55713)))
("SF_PLANTING" 0 ((14604.07240 908.74717) (14653.09242 904.97738)))
("SF_ARCHITECTURE" 0 ((14607.84355 5263.95215) (14622.92568 5250.07330) (14649.32127 5245.24604) (14728.50679
5248.86878)))
("SF_ARCHITECTURE" 0 ((14607.84355 5263.95215) (14619.15577 5271.33857) (14656.86233 5271.48699) (14671.94570
5267.87048) (14717.19457 5267.56810) (14728.50679 5260.18100)))
("SF_SOLAR" 0 ((14630.46799 8058.06946) (14611.61346 8061.84005)))
("SF_SOLAR" 0 ((14649.32127 8137.25498) (14648.12410 8129.70679) (14612.81199 8073.15238) (14611.61346 8061.84005)))
("SF_ARCHITECTURE" 0 ((14611.61346 5599.54751) (14630.46799 5599.54751)))
("SF_PLANTING" 0 ((14615.38462 3944.19265) (14619.37817 3887.56459) (14624.81188 3878.20554)))
("SF_ARCHITECTURE" 0 ((14615.38462 3944.19265) (14619.14887 3955.50554) (14619.30362 5075.41437) (14630.46753
5086.57262) (14630.46753 5090.34310) (14702.11120 5090.34966) (14766.21459 5082.95667)))
("SF_PLANTING" 0 ((14619.15577 3638.76278) (14617.95724 3650.07568) (14607.99140 3668.92952) (14608.90000 3680.24106)
(14615.38462 3691.55396)))
("SF_MASONRY_AND_ARCH" 0 ((14615.38462 3235.29412) (14619.14887 3182.50351) (14619.15577 2963.80090)))
("SF_PLANTING" 0 ((14690.79898 3239.06459) (14630.46799 3238.91686) (14615.38462 3235.29412)))
("SF_SOLAR" 0 ((14619.15577 7960.03020) (14619.15577 7952.48869)))
("SF_PLANTING" 0 ((14626.69683 3778.28054) (14619.15577 3789.59276)))
("SF_PLANTING" 0 ((14619.15577 3789.59276) (14656.86233 3798.33857) (14671.94570 3808.44604)))
("SF_MASONRY_AND_ARCH" 0 ((14619.15577 2963.80090) (14626.70373 2960.17817) (14664.40464 2960.03043)))
("SF_PLANTING" 0 ((14626.69683 1010.55713) (14630.31335 1040.72398) (14619.15577 1052.03620)))
("SF_PLANTING" 0 ((14619.15577 1052.03620) (14622.92568 1074.66063)))
("SF_SOLAR" 0 ((14837.85781 8005.27896) (14800.15124 8012.80747) (14724.73563 8012.67251) (14713.42342 8009.34593)
(14702.11120 8012.52443) (14687.02907 8009.20430) (14641.78020 8012.81403) (14622.92568 8009.04977)))
("SF_MASONRY_AND_ARCH" 0 ((14622.92568 1074.66063) (14619.16267 1202.86482) (14622.91878 1221.71946) (14622.93258
2168.17523) (14626.69683 2198.34061)))
("SF_PLANTING" 0 ((14622.92568 1074.66063) (14645.55011 1078.43043)))
("SF_PLANTING" 0 ((14671.94570 3815.98835) (14660.78122 3823.53563) (14635.29423 3853.69491) (14624.81188 3878.20554)))
("SF_PLANTING" 0 ((14624.81188 3878.20554) (14645.55011 3885.05238) (14660.63348 3895.17387)))
("SF_MASONRY_AND_ARCH" 0 ((15203.61991 2126.69683) (15184.76810 2127.75317) (15131.97545 2148.27183) (14928.35554
2204.83292) (14792.60894 2228.35905) (14754.90238 2228.65452) (14675.71686 2239.67127) (14626.69683 2239.66437)
(14615.53925 2232.27104) (14607.84310 2220.96505) (14616.44095 2205.88925) (14626.69683 2198.34061)))
("SF_MASONRY_AND_ARCH" 0 ((14626.69683 2198.34061) (14645.55011 2212.21991) (14683.25792 2213.27636) (14732.27794
2202.25962) (14788.83903 2202.11188)))
("SF_PLANTING" 0 ((14638.00905 980.39310) (14626.69683 1010.55713)))
("SF_PLANTING" 0 ((14630.46799 312.97229) (14623.08032 305.42296) (14626.69683 290.34785)))
("SF_PLANTING" 0 ((14641.78020 301.66007) (14634.23790 291.55124) (14626.69683 290.34785)))
("SF_SOLAR" 0 ((14638.00905 8076.92308) (14630.46799 8084.46448)))
("SF_ARCHITECTURE" 0 ((14660.63348 5595.77636) (14638.01595 5595.92477) (14630.46799 5599.54751)))
("SF_ARCHITECTURE" 0 ((14660.63348 5618.40113) (14649.32127 5618.40124) (14630.46799 5599.54751)))
("SF_PLANTING" 0 ((14641.78020 301.66007) (14630.46799 312.97229)))
("SF_PLANTING" 0 ((14641.78020 346.90894) (14631.52443 331.82410) (14630.46799 312.97229)))
("SF_SOLAR" 0 ((14641.78020 7993.96674) (14634.23790 7982.65452)))
("SF_PLANTING" 0 ((14638.00905 980.39310) (14634.23790 969.08088)))
("SF_PLANTING" 0 ((14638.00905 980.39310) (14656.86233 980.54016) (14679.48676 986.58088) (14694.57014 969.08088)))
("SF_MASONRY_AND_ARCH" 0 ((14641.78020 2522.62443) (14815.23337 2522.63066) (14868.02455 2526.39491)))
("SF_PLANTING" 0 ((14641.78020 301.66007) (14653.09242 306.48620) (14671.94570 323.08586) (14702.11120 331.82410)))
("SF_SOLAR" 0 ((14649.32127 8095.77670) (14645.55011 8103.31833)))
("SF_SOLAR" 0 ((14645.55011 8042.98643) (14694.57014 8039.22217) (14717.19457 8042.69027) (14732.27794 8039.22217)
(14826.54559 8039.22217) (14845.40011 8046.75724)))
("SF_SOLAR" 0 ((14664.40464 8163.65011) (14649.32127 8137.25498)))
("SF_PLANTING" 0 ((14653.09242 904.97738) (14675.71686 901.20758) (14717.19457 904.97738)))
("SF_PLANTING" 0 ((14694.57014 969.08088) (14653.45973 932.20848) (14653.09242 904.97738)))
("SF_PLANTING" 0 ((14717.19457 245.09898) (14694.57014 233.78586) (14653.09242 233.78586)))
("SF_PLANTING" 0 ((14653.09242 233.78586) (14654.29661 263.95079) (14675.71686 282.80543)))
("SF_SOLAR" 0 ((14883.10667 8058.06946) (14871.79446 8061.83348) (14687.02907 8061.83348) (14668.17455 8058.22398)
(14656.86233 8061.84005)))
("SF_PLANTING" 0 ((14660.63348 3895.17387) (14656.86233 3906.48609)))
("SF_SOLAR" 0 ((14664.40464 8035.44502) (14660.63348 8024.13281)))
("SF_ARCHITECTURE" 0 ((14660.63348 5618.40113) (14758.67229 5618.40113)))
("SF_ARCHITECTURE" 0 ((14660.63348 5618.40113) (14660.63348 5595.77636)))
("SF_ARCHITECTURE" 0 ((14660.63348 5595.77636) (14671.94570 5588.23529) (14732.27794 5595.77636) (15275.26584
5592.00600) (15297.89027 5592.00600) (15501.51018 5592.00600) (15520.36199 5592.00600) (15690.04525 5592.01267)
(15705.13009 5599.54751)))
("SF_PLANTING" 0 ((14660.63348 3895.17387) (14675.71686 3876.31934)))
("SF_MASONRY_AND_ARCH" 0 ((14660.63348 3163.65034) (14660.63348 3201.35747)))
("SF_SOLAR" 0 ((14664.40464 8163.65011) (14675.71686 8163.65011) (14943.43891 8163.65011)))
("SF_SOLAR" 0 ((14668.17455 8133.48416) (14664.40464 8141.02557)))
("SF_SOLAR" 0 ((14664.40464 7986.42534) (14664.40464 7993.96674)))
("SF_SOLAR" 0 ((14664.40464 7952.48869) (14664.40464 7963.80090)))
("SF_PLANTING" 0 ((14664.40464 3699.09502) (14679.48676 3695.47229) (14747.36007 3695.17602) (14758.67229 3691.55396)))
("SF_MASONRY_AND_ARCH" 0 ((14664.40464 3103.31799) (14664.25690 3027.90373) (14660.63348 3009.04977) (14664.40464
2990.19581)))
("SF_MASONRY_AND_ARCH" 0 ((14664.40464 2975.11312) (14664.40464 2960.03043)))
("SF_MASONRY_AND_ARCH" 0 ((14690.79898 2960.03043) (14679.48676 2956.26606) (14664.40464 2960.03043)))
("SF_PLANTING" 0 ((14668.17455 1093.51527) (14683.25792 1104.52364) (14702.10566 1093.50769) (14716.14514 1074.66063)
(14739.81900 1021.86934)))
("SF_PLANTING" 0 ((14671.94570 3815.98835) (14671.94570 3808.44604)))
("SF_PLANTING" 0 ((14671.94570 3815.98835) (14698.34129 3838.61278)))
("SF_PLANTING" 0 ((14690.79898 3800.90498) (14679.49367 3802.10260) (14671.94570 3808.44604)))
("SF_SOLAR" 0 ((14675.71686 8182.50385) (14675.71686 8174.96222)))
("SF_PLANTING" 0 ((14675.71686 1025.64197) (14690.79898 1029.39932) (14705.88235 1025.64197)))
("SF_PLANTING" 0 ((14698.34129 429.86425) (14684.31425 411.00962) (14683.10328 392.15781) (14675.71686 373.30317)))
("SF_SOLAR" 0 ((14901.96120 8107.08891) (14879.33676 8099.69548) (14819.00452 8099.39955) (14803.92115 8095.78326)
(14713.42342 8103.31176) (14683.25792 8099.54751)))
("SF_PLANTING" 0 ((14683.25792 460.03111) (14698.34129 471.34333)))
("SF_SOLAR" 0 ((14690.79898 8073.15226) (14690.79898 8080.69389)))
("SF_PLANTING" 0 ((14690.79898 3800.90498) (14717.19457 3797.14072) (14796.38009 3797.14072) (14819.00452 3804.67613)))
("SF_PLANTING" 0 ((14690.79898 3800.90498) (14690.79898 3751.88495)))
("SF_PLANTING" 0 ((14811.46346 3751.88495) (14720.96572 3751.87873) (14705.88235 3748.41097) (14690.79898 3751.88495)))
("SF_MASONRY_AND_ARCH" 0 ((14690.79898 3239.06459) (14690.79898 2960.03043)))
("SF_PLANTING" 0 ((14690.79898 3239.06459) (14720.96572 3239.06482) (14739.81900 3239.06482)))
("SF_MASONRY_AND_ARCH" 0 ((14736.04785 2960.03043) (14717.19457 2956.25916) (14690.79898 2960.03043)))
("SF_PLANTING" 0 ((14747.36007 984.16290) (14709.65351 970.12964) (14694.57014 969.08088)))
("SF_SOLAR" 0 ((14698.34129 8141.02557) (14698.34129 8156.10860)))
("SF_SOLAR" 0 ((14698.34129 8141.02557) (14803.92115 8141.03213) (14830.31674 8144.79638) (14905.73111 8144.64842)
(14920.81448 8141.02557)))
("SF_PLANTING" 0 ((14698.34129 3898.94378) (14709.65351 3902.71493)))
("SF_PLANTING" 0 ((14739.81900 3831.07048) (14713.42342 3831.22545) (14698.34129 3838.61278)))
("SF_PLANTING" 0 ((14720.96572 3868.77828) (14702.26584 3849.92500) (14698.34129 3838.61278)))
("SF_PLANTING" 0 ((14709.65351 467.57070) (14698.34129 471.34333)))
("SF_PLANTING" 0 ((14724.73563 505.27998) (14706.03699 493.96018) (14698.34129 471.34333)))
("SF_PLANTING" 0 ((14705.88235 324.28450) (14702.11120 331.82410)))
("SF_PLANTING" 0 ((14773.75566 412.89593) (14743.59016 394.87817) (14713.57805 369.53337) (14702.11120 331.82410)))
("SF_PLANTING" 0 ((14751.13122 275.26301) (14750.97658 301.66007) (14747.20532 309.05260) (14705.88235 324.28450)))
("SF_PLANTING" 0 ((14705.88235 324.28450) (14709.49887 301.66007) (14703.30973 267.72342) (14707.07952 256.41120)
(14717.19457 245.09898)))
("SF_SOLAR" 0 ((14709.65351 8174.96222) (14720.96572 8197.58665)))
("SF_SOLAR" 0 ((14709.65351 8024.13281) (14709.65351 8031.67421)))
("SF_SOLAR" 0 ((14709.65351 7952.48869) (14709.65351 7963.80090)))
("SF_PLANTING" 0 ((14717.19457 3898.94378) (14709.65351 3902.71493)))
("SF_PLANTING" 0 ((14717.19457 3932.88043) (14709.80826 3921.56821) (14709.65351 3902.71493)))
("SF_SOLAR" 0 ((14717.19457 8114.63054) (14724.73563 8133.48416)))
("SF_PLANTING" 0 ((14720.96572 3868.77828) (14717.19457 3898.94378)))
("SF_PLANTING" 0 ((14717.19457 3898.94378) (14736.04785 3910.25600)))
("SF_PLANTING" 0 ((14830.31674 908.74717) (14811.46346 901.21380) (14724.74253 901.35464) (14717.19457 904.97738)))
("SF_PLANTING" 0 ((14754.90238 984.16290) (14753.84604 961.53846) (14747.21222 950.22624) (14729.56312 934.99581)
(14717.19457 904.97738)))
("SF_PLANTING" 0 ((14728.50679 245.09898) (14717.19457 245.09898)))
("SF_PLANTING" 0 ((14720.96572 3868.77828) (14751.12432 3863.80984) (14758.67229 3857.46606)))
("SF_PLANTING" 0 ((14777.52681 456.25848) (14739.82590 482.80260) (14724.73563 505.27998)))
("SF_PLANTING" 0 ((14736.04785 531.67421) (14724.73563 505.27998)))
("SF_ARCHITECTURE" 0 ((14728.50679 5248.86878) (14728.50679 5260.18100)))
("SF_ARCHITECTURE" 0 ((14819.00452 5248.86878) (14807.69231 5256.25588) (14747.36007 5263.65566) (14728.50679
5260.18100)))
("SF_ARCHITECTURE" 0 ((14728.50679 5248.86878) (14743.59016 5238.76075) (14766.21459 5233.93382) (14815.23337
5233.78541)))
("SF_PLANTING" 0 ((14728.50679 245.09898) (14739.81900 233.78586) (14766.20769 233.78586) (14773.75566 233.78586)))
("SF_PLANTING" 0 ((14728.50679 245.09898) (14751.13122 275.26301)))
("SF_SOLAR" 0 ((14732.27794 8069.38167) (14736.04785 8080.69389)))
("SF_SOLAR" 0 ((14732.27794 7982.65452) (14732.27794 7997.73756)))
("SF_SOLAR" 0 ((14732.27794 7952.48869) (14732.27794 7960.03020)))
("SF_SOLAR" 0 ((14732.27794 7929.86425) (14732.27794 7918.55204)))
("SF_SOLAR" 0 ((14739.81900 8031.67421) (14736.04785 8024.13281)))
("SF_MASONRY_AND_ARCH" 0 ((14736.04785 2960.03043) (14803.92115 2960.03043)))
("SF_MASONRY_AND_ARCH" 0 ((14736.04785 2960.03043) (14739.81210 3005.27930) (14739.81900 3239.06482)))
("SF_PLANTING" 0 ((14803.92115 3239.06482) (14754.90238 3239.06482) (14739.81900 3239.06482)))
("SF_PLANTING" 0 ((14747.36007 984.16290) (14739.81900 1021.86934)))
("SF_PLANTING" 0 ((14739.81900 1021.86934) (14777.82240 1036.65034) (14788.69129 1067.11821) (14788.83903 1093.51527)))
("SF_PLANTING" 0 ((14766.21459 3951.73495) (14756.10656 3944.04480) (14754.53371 3922.77296) (14743.59016 3921.56821)))
("SF_PLANTING" 0 ((14747.36007 984.16290) (14754.90238 984.16290)))
("SF_PLANTING" 0 ((14751.13122 275.26301) (14768.78722 267.57500) (14773.75566 233.78586)))
("SF_SOLAR" 0 ((14754.90238 8118.40113) (14754.90238 8133.48416)))
("SF_SOLAR" 0 ((14754.90238 7952.48869) (14754.90238 7963.80090)))
("SF_PLANTING" 0 ((14800.15124 986.04921) (14766.21459 987.78563) (14754.90238 984.16290)))
("SF_SOLAR" 0 ((14766.21459 7929.86425) (14762.44344 7914.78133)))
("SF_SOLAR" 0 ((14766.21459 7982.65452) (14766.21459 7993.96674)))
("SF_SOLAR" 0 ((14811.46346 7865.76165) (14792.60339 7846.01301) (14766.21459 7843.13722)))
("SF_ARCHITECTURE" 0 ((15165.91210 4969.83450) (15139.51776 4974.66109) (15015.08337 5017.79785) (14996.22885
5019.00170) (14917.04333 5041.32986) (14894.41889 5042.53439) (14871.79446 5052.64208) (14845.40011 5052.93835)
(14815.23337 5063.95430) (14777.53235 5068.02794) (14771.04084 5071.79842) (14766.21459 5082.95667)))
("SF_ARCHITECTURE" 0 ((14766.21459 5082.95667) (14773.76256 5089.15204) (14830.31674 5086.57873) (14849.17002
5079.33360) (14947.21007 5063.04672) (15161.99310 4995.02500) (15169.68326 4984.91663)))
("SF_PLANTING" 0 ((14766.21459 3951.73495) (14785.06787 3944.34106) (14807.69231 3943.14310) (14834.08790 3933.02885)
(14852.94118 3932.88043)))
("SF_PLANTING" 0 ((14766.21459 3951.73495) (14785.21561 3984.61493) (14803.92115 3989.29367) (14844.20158 3974.20441)
(14852.94118 3932.88043)))
("SF_SOLAR" 0 ((14769.98450 8114.63054) (14792.60894 8118.24661) (14819.00452 8114.63054)))
("SF_PLANTING" 0 ((14769.98450 3834.84163) (14777.53371 3831.21889) (14807.69231 3831.07048)))
("SF_PLANTING" 0 ((14773.75566 412.89593) (14787.78269 384.61538) (14792.60894 346.90894)))
("SF_PLANTING" 0 ((14777.52681 456.25848) (14773.75566 412.89593)))
("SF_PLANTING" 0 ((14819.00452 422.32183) (14785.06787 418.40079) (14773.75566 412.89593)))
("SF_PLANTING" 0 ((14773.75566 321.76991) (14782.49389 339.35962) (14792.60894 346.90894)))
("SF_PLANTING" 0 ((14773.75566 233.78586) (14781.30362 233.78586) (14819.00452 233.78586) (14843.51391 254.52489)))
("SF_SOLAR" 0 ((14777.52681 8084.46448) (14777.52681 8076.92308)))
("SF_SOLAR" 0 ((14777.52681 8024.13281) (14777.52681 8031.67421)))
("SF_PLANTING" 0 ((14819.00452 422.32183) (14817.95509 441.17647) (14807.68541 459.86878) (14800.15124 462.59604)
(14777.52681 456.25848)))
("SF_SOLAR" 0 ((14785.06787 7956.25939) (14785.06787 7963.80090)))
("SF_PLANTING" 0 ((14807.69231 3853.69491) (14790.03631 3865.01403) (14785.36335 3880.08428) (14788.83903 3887.63156)))
("SF_SOLAR" 0 ((14800.15124 7944.94717) (14792.60894 7948.71799)))
("SF_ARCHITECTURE" 0 ((14792.60894 4219.45701) (14899.24638 4377.82805) (14992.45894 4502.26244)))
("SF_PLANTING" 0 ((14800.15124 986.04921) (14792.60894 961.53846)))
("SF_PLANTING" 0 ((14792.60894 346.90894) (14799.10735 342.98303) (14810.55486 324.28450) (14820.20871 290.35271)
(14837.85781 275.26301)))
("SF_SOLAR" 0 ((14800.15124 8069.38167) (14800.15124 8076.92308)))
("SF_SOLAR" 0 ((14800.15124 7982.65452) (14800.15124 7993.96674)))
("SF_SOLAR" 0 ((14815.23337 7892.15690) (14807.69231 7892.15690) (14800.15124 7899.69830)))
("SF_PLANTING" 0 ((14800.15124 986.04921) (14819.00452 976.76889) (14856.71233 972.85068)))
("SF_PLANTING" 0 ((14800.15124 986.04921) (14819.75158 1014.32975) (14819.00452 1025.64197)))
("SF_PLANTING" 0 ((14868.02455 3239.06482) (14860.47534 3239.06482) (14803.92115 3239.06482)))
("SF_MASONRY_AND_ARCH" 0 ((14803.92115 3239.06482) (14807.69231 3216.44016) (14803.92805 3190.04525) (14803.92115
2960.03043)))
("SF_MASONRY_AND_ARCH" 0 ((14834.08790 2960.03043) (14803.92115 2960.03043)))
("SF_PLANTING" 0 ((14807.69231 3831.07048) (14807.69231 3853.69491)))
("SF_PLANTING" 0 ((14807.69231 3853.69491) (14822.77568 3865.00713)))
("SF_PLANTING" 0 ((14819.00452 3804.67613) (14814.03609 3823.52319) (14807.69231 3831.07048)))
("SF_SOLAR" 0 ((15071.64446 7865.76165) (15052.78993 7855.50577) (14826.54559 7854.60407) (14811.46346 7865.76165)))
("SF_SOLAR" 0 ((14811.46346 7865.76165) (14815.23337 7892.15690)))
("SF_PLANTING" 0 ((14811.46346 3751.88495) (14807.84695 3736.80283) (14811.46346 3725.49061)))
("SF_PLANTING" 0 ((14811.46346 3751.88495) (14845.39321 3759.27229) (14851.88484 3755.50147) (14856.41550 3744.34389)
(14837.70305 3702.87240) (14830.31674 3696.52862) (14815.23337 3695.32387)))
("SF_MASONRY_AND_ARCH" 0 ((14811.46346 2190.79966) (14852.94118 2190.65113) (14879.33676 2180.53688) (14909.50226
2179.33891) (14935.89785 2169.22466) (15003.77115 2155.66505) (15022.62443 2146.60023) (15045.24887 2144.35283)
(15147.05882 2110.55769) (15192.30769 2090.04604) (15207.39253 2087.93326) (15248.86878 2066.36527)))
("SF_SOLAR" 0 ((14815.23337 7892.15690) (14833.03156 7903.47568) (14884.16301 7990.19615) (14897.13371 8005.27896)
(14959.57183 8114.63054) (14983.86018 8148.56719) (14992.31120 8167.42081) (14988.68778 8190.04525)))
("SF_SOLAR" 0 ((14826.54559 7843.13722) (14815.23337 7843.13722)))
("SF_ARCHITECTURE" 0 ((14815.23337 5233.78541) (14830.31674 5223.52986) (14849.17002 5222.62161) (14864.09876
5227.44197) (14871.79446 5241.32771)))
("SF_ARCHITECTURE" 0 ((14819.00452 5248.86878) (14815.23337 5233.78541)))
("SF_PLANTING" 0 ((14815.23337 1052.03620) (14828.06312 1067.11821) (14827.74412 1097.28507) (14852.63880 1127.45192)
(14852.94118 1138.76414)))
("SF_ARCHITECTURE" 0 ((14819.00452 5248.86878) (14871.79446 5241.32771)))
("SF_PLANTING" 0 ((14819.00452 3804.67613) (14879.33959 3804.82398) (14892.53394 3808.44604)))
("SF_PLANTING" 0 ((14819.00452 422.32183) (14847.28507 386.50170)))
("SF_SOLAR" 0 ((14822.77568 8076.92308) (14822.77568 8069.38167)))
("SF_MASONRY_AND_ARCH" 0 ((15030.16550 1602.56505) (14822.77568 1293.36256)))
("SF_PLANTING" 0 ((14822.77568 1131.22172) (14834.08790 1153.84615)))
("SF_SOLAR" 0 ((14830.31674 8024.13281) (14830.31674 8031.67421)))
("SF_PLANTING" 0 ((14830.31674 908.74717) (14830.31674 916.28959)))
("SF_PLANTING" 0 ((14830.31674 908.74717) (14852.94118 901.35464) (14883.10667 901.35532) (14905.73111 916.28959)))
("SF_MASONRY_AND_ARCH" 0 ((14834.08790 3205.12794) (14834.08790 3152.33812)))
("SF_MASONRY_AND_ARCH" 0 ((14834.08790 3061.84038) (14830.61222 3012.82025) (14834.08790 2960.03043)))
("SF_MASONRY_AND_ARCH" 0 ((14868.02455 2960.03043) (14834.08790 2960.03043)))
("SF_PLANTING" 0 ((14834.08790 377.07296) (14847.28507 386.50170)))
("SF_SOLAR" 0 ((14837.85781 8114.63054) (14852.94118 8114.63054)))
("SF_PLANTING" 0 ((14843.51391 254.52489) (14838.08009 263.88382) (14837.85781 275.26301)))
("SF_PLANTING" 0 ((14888.76278 305.42986) (14864.25339 300.46143) (14837.85781 275.26301)))
("SF_SOLAR" 0 ((14841.62896 7967.57172) (14852.94118 7960.03020)))
("SF_PLANTING" 0 ((14928.35554 252.63857) (14917.03778 242.52500) (14905.73111 233.78586) (14879.33676 233.78586)
(14860.48224 242.37726) (14843.51391 254.52489)))
("SF_PLANTING" 0 ((14888.76278 305.42986) (14874.50928 282.95317) (14843.51391 254.52489)))
("SF_SOLAR" 0 ((14845.40011 7899.69830) (14860.48224 7903.46912) (15067.87330 7903.46256) (15079.18552 7899.69830)))
("SF_PLANTING" 0 ((14847.28507 386.50170) (14852.94118 380.84559) (14860.48224 380.84559)))
("SF_PLANTING" 0 ((14847.28507 386.50170) (14864.26029 406.18348) (14879.33676 411.00962)))
("SF_PLANTING" 0 ((14849.17002 1044.49378) (14860.63688 1018.09955) (14879.33676 1003.01753)))
("SF_PLANTING" 0 ((14852.94118 3989.44152) (14875.41787 4000.90871) (14885.82839 4015.83710) (14893.22161 4038.46154)
(14890.64898 4057.31482)))
("SF_PLANTING" 0 ((14860.48224 3921.56821) (14852.94118 3932.88043)))
("SF_SOLAR" 0 ((14856.71233 8069.38167) (14856.71233 8076.92308)))
("SF_PLANTING" 0 ((14856.71233 972.85068) (14883.10667 972.85068)))
("SF_PLANTING" 0 ((14860.48224 987.93269) (14856.71233 972.85068)))
("SF_ARCHITECTURE" 0 ((14860.48224 4415.53586) (14895.47523 4468.32579) (14923.38846 4498.49129) (14952.03631
4547.51131) (15014.02704 4622.92568) (15060.33224 4698.34129)))
("SF_PLANTING" 0 ((14860.48224 3921.56821) (14928.35554 3917.79830)))
("SF_PLANTING" 0 ((14860.48224 3921.56821) (14860.48224 3906.48609)))
("SF_PLANTING" 0 ((14886.87783 3853.69491) (14880.23167 3880.09050) (14860.48224 3906.48609)))
("SF_PLANTING" 0 ((14886.87783 3853.69491) (14852.94118 3855.94921) (14842.83314 3865.00781) (14839.20962 3887.48371)
(14860.48224 3906.48609)))
("SF_PLANTING" 0 ((14888.76278 305.42986) (14860.48224 380.84559)))
("SF_PLANTING" 0 ((14860.48224 380.84559) (14878.13269 395.92760) (14879.33676 411.00962)))
("SF_SOLAR" 0 ((14868.02455 7937.40577) (15090.49774 7937.40577)))
("SF_PLANTING" 0 ((14868.02455 3239.06482) (14905.73111 3239.06482) (14939.66776 3239.06482)))
("SF_MASONRY_AND_ARCH" 0 ((14868.02455 2960.03043) (14868.03145 3167.42081) (14871.49887 3182.50351) (14868.02455
3239.06482)))
("SF_MASONRY_AND_ARCH" 0 ((14868.02455 2960.03043) (14928.34864 2960.17817) (14935.89785 2963.80090)))
("SF_ARCHITECTURE" 0 ((14871.79446 5241.32771) (15094.26889 5183.70995) (15316.74208 5102.85973) (15365.76357
5090.49774)))
("SF_PLANTING" 0 ((14898.19005 1006.78733) (14898.03541 1033.18156) (14885.67364 1067.11335) (14871.79446 1074.66063)))
("SF_ARCHITECTURE" 0 ((14883.10667 5211.16097) (14875.56561 5211.16097)))
("SF_MASONRY_AND_ARCH" 0 ((14879.33676 1489.44287) (14917.19242 1545.99638) (14934.84152 1561.09219) (14985.96606
1644.04129) (15044.19253 1719.45701) (15101.80995 1809.95475)))
("SF_PLANTING" 0 ((14883.10667 972.85068) (14879.33676 1003.01753)))
("SF_PLANTING" 0 ((14898.19005 1006.78733) (14879.33676 1003.01753)))
("SF_PLANTING" 0 ((14879.33676 411.00962) (14886.87783 433.63405)))
("SF_SOLAR" 0 ((14883.10667 8058.06946) (14900.90486 8080.69389) (14943.43891 8163.65011)))
("SF_SOLAR" 0 ((14883.10667 7963.80090) (14894.41889 7961.23450) (14913.27342 7970.13812) (14981.14672 7967.57828)
(15000.00000 7971.33575) (15113.12217 7971.34231)))
("SF_SOLAR" 0 ((14883.10667 7926.09355) (14883.10667 7918.55204)))
("SF_PLANTING" 0 ((14883.10667 972.85068) (14909.50226 953.99604)))
("SF_SOLAR" 0 ((14890.64898 8133.48416) (14886.87783 8118.40113)))
("SF_ARCHITECTURE" 0 ((14886.87783 5618.40113) (14894.41889 5618.40113) (14901.96120 5618.40113) (15671.19344
5618.39457) (15693.81787 5613.42613) (15705.13009 5599.54751)))
("SF_PLANTING" 0 ((14894.41889 3838.61278) (14886.87783 3846.15385) (14886.87783 3853.69491)))
("SF_PLANTING" 0 ((14905.73111 916.28959) (14886.87783 935.14423)))
("SF_PLANTING" 0 ((14924.58563 392.15781) (14916.88857 418.55204) (14905.73111 428.66629) (14886.87783 433.63405)))
("SF_PLANTING" 0 ((14886.87783 433.63405) (14890.79683 490.19514) (14898.19005 505.27998)))
("SF_PLANTING" 0 ((14888.76278 305.42986) (14928.35554 305.42986)))
("SF_MASONRY_AND_ARCH" 0 ((14890.64898 3042.98643) (14890.64898 2997.73756)))
("SF_MASONRY_AND_ARCH" 0 ((15124.43439 2530.16618) (15105.58111 2522.92059) (15090.49774 2526.38869) (14984.91663
2526.39491) (14962.29219 2522.63066) (14913.27342 2522.77217) (14898.19695 2526.24027) (14890.64898 2522.62443)))
("SF_PLANTING" 0 ((15003.77115 3736.80283) (14998.79581 3755.65611) (14988.47376 3770.37704) (14917.04333 3794.41312)
(14892.53394 3808.44604)))
("SF_PLANTING" 0 ((14913.27342 3733.03167) (14898.19695 3744.35011) (14890.80373 3755.65611) (14892.53394 3808.44604)))
("SF_PLANTING" 0 ((14892.53394 3808.44604) (14894.41889 3838.61278)))
("SF_PLANTING" 0 ((14928.35554 3846.15385) (14909.50226 3845.99921) (14894.41889 3838.61278)))
("SF_MASONRY_AND_ARCH" 0 ((14898.19005 3205.12794) (14898.19005 3193.81572)))
("SF_MASONRY_AND_ARCH" 0 ((14898.19005 2360.48292) (14917.04333 2360.48292)))
("SF_PLANTING" 0 ((14898.19005 1006.78733) (14913.12432 999.09163) (14924.43100 980.39310) (14923.38156 969.08088)
(14909.50226 953.99604)))
("SF_SOLAR" 0 ((14909.50226 8050.52783) (14901.96120 8061.84005)))
("SF_PLANTING" 0 ((14905.73111 3601.05554) (14924.58563 3623.68066)))
("SF_PLANTING" 0 ((14917.04333 916.28959) (14905.73111 916.28959)))
("SF_SOLAR" 0 ((15135.74661 8005.27896) (15056.56109 8005.42715) (15037.70781 8012.52421) (15018.85328 8005.42715)
(14947.21007 8009.04966) (14909.50226 8005.27896)))
("SF_PLANTING" 0 ((14917.04333 931.37161) (14909.50226 953.99604)))
("SF_SOLAR" 0 ((14913.27342 7990.19615) (14917.04333 7978.88394)))
("SF_SOLAR" 0 ((14913.27342 7918.55204) (14913.27342 7929.86425)))
("SF_PLANTING" 0 ((14924.58563 3944.19265) (14913.27342 3951.73495)))
("SF_MASONRY_AND_ARCH" 0 ((15256.40837 2658.37104) (15248.86188 2665.91256) (15177.22285 2665.91256) (15162.14219
2665.91256) (15082.95667 2665.91256) (15064.10215 2665.91256) (14977.37557 2665.91256) (14943.43891 2665.91256)
(14913.27342 2665.91256)))
("SF_MASONRY_AND_ARCH" 0 ((14913.27342 2665.91256) (14913.27342 2631.97590)))
("SF_MASONRY_AND_ARCH" 0 ((15256.40837 2631.97590) (15245.09615 2631.97590) (15158.37104 2631.97590) (15150.82998
2631.97590) (15101.80995 2631.97590) (14913.27342 2631.97590)))
("SF_SOLAR" 0 ((14920.81448 8073.15226) (14917.04333 8080.69389)))
("SF_PLANTING" 0 ((14917.04333 3684.01165) (14939.66776 3691.55396)))
("SF_PLANTING" 0 ((14917.04333 916.28959) (14917.04333 931.37161)))
("SF_PLANTING" 0 ((14969.83450 946.45645) (14939.66776 941.63507) (14917.04333 931.37161)))
("SF_PLANTING" 0 ((14917.04333 916.28959) (14939.66776 901.35532) (14973.60441 901.36086) (14988.68778 912.51980)))
("SF_SOLAR" 0 ((14920.81448 8182.50385) (14920.81448 8174.96222)))
("SF_SOLAR" 0 ((14920.81448 8095.77670) (14932.12670 8092.00611)))
("SF_PLANTING" 0 ((14924.58563 3944.19265) (14928.35554 3917.79830)))
("SF_PLANTING" 0 ((14924.58563 3944.19265) (14949.78269 3974.35939) (14955.95532 4000.74751) (14966.06335 4007.99265)
(14988.68778 3996.83541) (15033.93665 3944.19265)))
("SF_PLANTING" 0 ((14939.66776 3917.79830) (14928.35554 3917.79830)))
("SF_PLANTING" 0 ((14928.35554 3846.15385) (14966.06335 3813.27387) (14981.14672 3808.44604)))
("SF_PLANTING" 0 ((14928.35554 3846.15385) (14939.66776 3856.26188) (15011.31222 3876.17149) (15045.24887 3872.54943)))
("SF_MASONRY_AND_ARCH" 0 ((15026.39559 2326.54627) (15022.46980 2332.89005) (14984.91663 2338.01312) (14958.52229
2349.02296) (14928.35554 2349.17070)))
("SF_PLANTING" 0 ((14928.35554 305.42986) (14928.35554 271.49321)))
("SF_PLANTING" 0 ((14928.35554 305.42986) (14933.33088 335.59672) (14946.15373 350.67873) (14963.34853 388.38518)
(14988.69468 418.54581) (15003.77115 429.86425)))
("SF_PLANTING" 0 ((14973.60441 263.95079) (14947.21007 271.34548) (14928.35554 271.49321)))
("SF_PLANTING" 0 ((14928.35554 252.63857) (14928.35554 271.49321)))
("SF_PLANTING" 0 ((15033.93665 252.63857) (14981.14672 233.78586) (14950.97998 233.78586) (14928.35554 252.63857)))
("SF_PLANTING" 0 ((14939.66776 3910.25600) (14935.89785 3910.25600) (14932.12670 3902.71493)))
("SF_PLANTING" 0 ((14932.12670 3729.26052) (14943.29118 3728.05667) (14950.97998 3717.94830)))
("SF_SOLAR" 0 ((14935.89785 7948.71799) (14935.89785 7956.25939)))
("SF_MASONRY_AND_ARCH" 0 ((14935.89785 2963.80090) (14943.44581 2960.17817) (15000.00000 2960.03043)))
("SF_MASONRY_AND_ARCH" 0 ((14935.89785 2963.80090) (14935.90475 3186.27477) (14939.66776 3239.06482)))
("SF_SOLAR" 0 ((14939.66776 8061.84005) (15177.22285 8058.06946)))
("SF_PLANTING" 0 ((14939.66776 3910.25600) (14939.66776 3917.79830)))
("SF_PLANTING" 0 ((14981.14672 3951.73495) (14977.22093 3941.47817) (14939.66776 3917.79830)))
("SF_PLANTING" 0 ((14939.66776 3910.25600) (14954.75113 3902.86957) (15000.00000 3914.02715)))
("SF_PLANTING" 0 ((14988.68778 3714.17839) (14983.71934 3691.55396) (14969.83450 3677.68133) (14962.29219 3677.53348)
(14939.66776 3691.55396)))
("SF_PLANTING" 0 ((14950.97998 3717.94830) (14939.66776 3691.55396)))
("SF_PLANTING" 0 ((14996.22885 3239.06482) (14981.14672 3239.06482) (14939.66776 3239.06482)))
("SF_SOLAR" 0 ((14981.14672 8193.81606) (14943.43891 8163.65011)))
("SF_SOLAR" 0 ((14950.97998 8035.44502) (14952.86618 8026.01810) (14947.21007 8027.90339) (14943.43891 8024.13281)))
("SF_SOLAR" 0 ((15041.47771 8031.67421) (15026.38869 8042.82523) (15007.54106 8039.37025) (14996.22885 8042.83846)
(14947.21007 8042.98643)))
("SF_SOLAR" 0 ((14947.21007 7978.88394) (14954.75113 7990.19615)))
("SF_PLANTING" 0 ((14950.97998 3717.94830) (14981.13982 3717.80045) (14988.68778 3714.17839)))
("SF_PLANTING" 0 ((14969.83450 3627.45057) (14962.29219 3627.45057)))
("SF_SOLAR" 0 ((14966.06335 8099.54751) (14977.37557 8103.17025) (15075.41437 8103.32489) (15094.26889 8107.07579)
(15199.84729 8099.54751)))
("SF_SOLAR" 0 ((14966.06335 7918.55204) (14969.83450 7929.86425)))
("SF_SOLAR" 0 ((14969.83450 7944.94717) (14973.60441 7956.25939)))
("SF_PLANTING" 0 ((14988.68778 912.51980) (14969.83450 946.45645)))
("SF_PLANTING" 0 ((14969.83450 946.45645) (14973.60441 972.85068)))
("SF_SOLAR" 0 ((14973.60441 8076.92308) (14973.60441 8069.38167)))
("SF_PLANTING" 0 ((14973.60441 972.85068) (14958.67704 991.70532) (14959.57873 1003.01753) (14966.21109 1014.17443)
(14992.30430 1022.02466) (14997.43292 1040.71708) (15003.77805 1047.06154) (15041.47771 1048.26640)))
("SF_PLANTING" 0 ((15026.39559 984.16290) (14973.60441 972.85068)))
("SF_SOLAR" 0 ((14988.68778 7990.19615) (14981.14672 7978.88394)))
("SF_PLANTING" 0 ((15000.00000 3819.75826) (14984.91663 3834.84163)))
("SF_MASONRY_AND_ARCH" 0 ((15000.00000 3190.04525) (14984.91663 3190.04525)))
("SF_PLANTING" 0 ((15003.77115 3736.80283) (14995.17930 3718.10328) (14988.68778 3714.17839)))
("SF_PLANTING" 0 ((14988.68778 912.51980) (15007.54106 912.51980)))
("SF_SOLAR" 0 ((15233.78394 8141.02557) (15003.77115 8141.03213) (14992.45894 8144.79638)))
("SF_SOLAR" 0 ((15003.77115 8031.67421) (14996.22885 8024.13281)))
("SF_PLANTING" 0 ((15033.93665 3239.06482) (15003.77805 3239.06482) (14996.22885 3239.06482)))
("SF_PLANTING" 0 ((15000.00000 3190.04525) (14999.85226 3223.98190) (14996.22885 3239.06482)))
("SF_SOLAR" 0 ((15000.00000 8163.65000) (15233.78394 8163.64344) (15245.09615 8159.87941)))
("SF_MASONRY_AND_ARCH" 0 ((15000.00000 3190.04525) (15000.00000 2960.03043)))
("SF_MASONRY_AND_ARCH" 0 ((15000.00000 2960.03043) (15033.93665 2960.03043)))
("SF_PLANTING" 0 ((15000.00000 444.94627) (15003.77115 429.86425)))
("SF_SOLAR" 0 ((15007.54106 8220.21109) (15003.77115 8227.75271)))
("SF_SOLAR" 0 ((15007.54106 8133.48416) (15003.77115 8118.40113)))
("SF_SOLAR" 0 ((15003.77115 7914.78133) (15003.77115 7929.86425)))
("SF_PLANTING" 0 ((15067.87330 3755.65611) (15030.16550 3741.62907) (15003.77115 3736.80283)))
("SF_PLANTING" 0 ((15049.02002 388.38518) (15019.00792 403.61708) (15003.77115 429.86425)))
("SF_SOLAR" 0 ((15011.31222 7960.03020) (15007.54106 7948.71799)))
("SF_PLANTING" 0 ((15098.03880 912.51980) (15079.18552 912.37138) (15045.24887 901.20758) (15022.62443 902.26324)
(15007.54106 912.51980)))
("SF_PLANTING" 0 ((15030.16550 969.08088) (15029.10905 950.22624) (15007.54106 912.51980)))
("SF_PLANTING" 0 ((15018.85328 343.13631) (15011.31222 343.13631)))
("SF_PLANTING" 0 ((15015.08337 3797.13382) (15030.16550 3789.59898) (15041.47081 3790.79038) (15049.02002 3797.13382)))
("SF_PLANTING" 0 ((15026.39559 297.88744) (15018.85328 343.13631)))
("SF_PLANTING" 0 ((15049.02002 350.67873) (15030.16550 349.62240) (15018.85328 343.13631)))
("SF_SOLAR" 0 ((15022.62443 7982.65452) (15026.39559 7993.96674)))
("SF_MASONRY_AND_ARCH" 0 ((15309.20249 2239.81900) (15297.89027 2247.20611) (15275.26584 2248.56482) (15263.95362
2257.46878) (15241.32919 2259.87704) (15230.01697 2268.78100) (15173.45588 2282.50147) (15162.14219 2291.40543)
(15105.58111 2304.97817) (15049.02002 2325.49604) (15026.39559 2326.54627)))
("SF_MASONRY_AND_ARCH" 0 ((15026.39559 2319.00452) (15026.39559 2326.54627)))
("SF_PLANTING" 0 ((15026.39559 984.16290) (15030.16550 980.39310) (15030.16550 969.08088)))
("SF_PLANTING" 0 ((15052.78993 1010.55713) (15037.71471 1002.86912) (15026.39559 984.16290)))
("SF_PLANTING" 0 ((15026.39559 520.36199) (15033.93665 520.05962) (15040.27353 512.81957) (15041.62545 463.80090)
(15055.50475 426.09446) (15060.33224 399.69740)))
("SF_PLANTING" 0 ((15026.39559 297.88744) (15036.50373 290.34027) (15041.47771 260.18100)))
("SF_PLANTING" 0 ((15033.93665 252.63857) (15019.00792 271.49321) (15020.05045 290.34027) (15026.39559 297.88744)))
("SF_SOLAR" 0 ((15030.16550 8182.50385) (15030.16550 8174.96222)))
("SF_PLANTING" 0 ((15105.58111 972.85068) (15071.64446 976.47342) (15030.16550 969.08088)))
("SF_SOLAR" 0 ((15033.93665 8118.40113) (15037.70781 8129.71335)))
("SF_PLANTING" 0 ((15033.93665 3944.19265) (15038.76425 3906.48609) (15049.02002 3887.63156)))
("SF_PLANTING" 0 ((15033.93665 3944.19265) (15052.78993 3947.96380)))
("SF_PLANTING" 0 ((15033.93665 3239.06482) (15071.64446 3239.06482)))
("SF_MASONRY_AND_ARCH" 0 ((15033.93665 3239.06482) (15033.93665 2960.03043)))
("SF_MASONRY_AND_ARCH" 0 ((15067.87330 2960.03043) (15033.93665 2960.03043)))
("SF_PLANTING" 0 ((15033.93665 252.63857) (15041.47771 252.63857)))
("SF_SOLAR" 0 ((15045.24887 8080.69389) (15037.70781 8069.38167)))
("SF_PLANTING" 0 ((15037.70781 1074.66063) (15041.47771 1048.26640)))
("SF_SOLAR" 0 ((15060.33224 8088.23529) (15041.47771 8088.23529)))
("SF_PLANTING" 0 ((15052.78993 1044.49378) (15041.47771 1048.26640)))
("SF_PLANTING" 0 ((15041.47771 260.18100) (15041.47771 252.63857)))
("SF_PLANTING" 0 ((15071.64446 275.26301) (15041.47771 260.18100)))
("SF_PLANTING" 0 ((15109.35102 233.78676) (15086.72658 230.02794) (15064.10215 233.78586) (15041.47771 252.63857)))
("SF_SOLAR" 0 ((15045.24887 8024.13281) (15064.10215 8042.98643)))
("SF_PLANTING" 0 ((15045.24887 3853.69491) (15045.24887 3872.54943)))
("SF_PLANTING" 0 ((15049.02002 3887.63156) (15049.02002 3876.31934) (15045.24887 3872.54943)))
("SF_PLANTING" 0 ((15045.24887 3853.69491) (15094.26889 3833.79186) (15120.66324 3818.70283) (15135.74661 3804.67613)))
("SF_PLANTING" 0 ((15049.02002 3797.13382) (15041.62545 3823.52941) (15041.62545 3849.77002) (15045.24887 3853.69491)))
("SF_PLANTING" 0 ((15049.02002 3887.63156) (15082.95667 3891.40271)))
("SF_PLANTING" 0 ((15049.02002 3797.13382) (15060.18450 3789.58654) (15071.64446 3770.73948)))
("SF_PLANTING" 0 ((15049.02002 350.67873) (15049.02002 388.38518)))
("SF_PLANTING" 0 ((15060.33224 399.69740) (15049.02002 388.38518)))
("SF_PLANTING" 0 ((15071.64446 275.26301) (15070.58812 305.42986) (15059.27590 339.36652) (15049.02002 350.67873)))
("SF_PLANTING" 0 ((15120.66324 3684.01165) (15115.83699 3653.84615) (15101.80995 3635.14683) (15067.87330 3623.82851)
(15052.78993 3623.68066)))
("SF_PLANTING" 0 ((15052.78993 1010.55713) (15052.78993 1044.49378)))
("SF_PLANTING" 0 ((15052.78993 1044.49378) (15075.25962 1053.22726) (15079.18552 1059.57862)))
("SF_PLANTING" 0 ((15052.78993 1010.55713) (15103.69491 1008.67364)))
("SF_SOLAR" 0 ((15056.56109 7982.65452) (15060.33224 7990.19615)))
("SF_SOLAR" 0 ((15060.33224 7926.09355) (15056.56109 7914.78133)))
("SF_SOLAR" 0 ((15056.56109 7843.13722) (15082.95667 7846.90803)))
("SF_PLANTING" 0 ((15060.33224 399.69740) (15075.41437 399.69740)))
("SF_SOLAR" 0 ((15067.87330 8133.48416) (15067.87330 8122.17195) (15064.10215 8118.40113)))
("SF_ARCHITECTURE" 0 ((15064.10215 5720.21109) (15075.41437 5710.10294) (15211.15950 5709.05351) (15226.24434
5720.21109)))
("SF_ARCHITECTURE" 0 ((15064.10215 5720.21109) (15079.18552 5734.08959) (15211.15950 5735.13948) (15218.69638
5731.36855) (15226.24434 5720.21109)))
("SF_PLANTING" 0 ((15131.97545 3725.49061) (15124.42749 3718.10328) (15082.96357 3722.92398) (15076.61844 3729.26742)
(15067.87330 3755.65611)))
("SF_PLANTING" 0 ((15067.87330 3755.65611) (15071.64446 3770.73948)))
("SF_MASONRY_AND_ARCH" 0 ((15067.87330 2960.03043) (15105.58111 2960.03043)))
("SF_MASONRY_AND_ARCH" 0 ((15067.87330 2960.03043) (15068.02104 3027.90373) (15071.63756 3042.98643) (15071.64446
3239.06482)))
("SF_SOLAR" 0 ((15071.64446 7865.76165) (15090.49774 7854.59751) (15131.97545 7850.68529) (15158.37104 7854.29480)
(15177.22285 7850.67873) (15282.80543 7854.60407) (15297.89027 7865.76165)))
("SF_SOLAR" 0 ((15071.64446 7865.76165) (15072.84174 7873.30973) (15086.73348 7892.00882) (15116.89333 7903.32104)
(15656.10860 7904.67342) (15677.68360 7929.86425) (15867.26810 8223.98190)))
("SF_PLANTING" 0 ((15135.74661 3789.59276) (15120.65769 3775.71414) (15101.80995 3770.88733) (15071.64446 3770.73948)))
("SF_PLANTING" 0 ((15105.58111 3239.06482) (15071.64446 3239.06482)))
("SF_PLANTING" 0 ((15071.64446 275.26301) (15101.80995 275.26301)))
("SF_PLANTING" 0 ((15086.72658 3533.18224) (15075.41437 3525.64129)))
("SF_PLANTING" 0 ((15090.49774 354.44853) (15084.15396 361.99785) (15075.41437 399.69740)))
("SF_PLANTING" 0 ((15128.20554 426.09446) (15075.41437 399.69740)))
("SF_SOLAR" 0 ((15079.18552 7948.71799) (15079.18552 7956.25939)))
("SF_PLANTING" 0 ((15086.72658 1112.36708) (15079.33326 1101.05486) (15076.61154 1089.75023) (15079.18552 1082.20305)))
("SF_SOLAR" 0 ((15109.35102 8088.23529) (15094.27443 8087.03100) (15082.95667 8069.38167)))
("SF_SOLAR" 0 ((15082.95667 8016.59118) (15084.16086 8024.13937) (15094.26889 8035.44502)))
("SF_PLANTING" 0 ((15109.35102 3865.00713) (15090.64548 3876.32624) (15082.95667 3891.40271)))
("SF_PLANTING" 0 ((15147.05882 3880.09050) (15139.51086 3881.29502) (15116.89333 3898.78982) (15094.26889 3898.78982)
(15082.95667 3891.40271)))
("SF_PLANTING" 0 ((15086.72658 3985.67161) (15131.97545 3993.21267)))
("SF_PLANTING" 0 ((15090.49774 354.44853) (15091.70192 320.51188) (15105.58111 305.42986)))
("SF_PLANTING" 0 ((15090.49774 354.44853) (15101.80995 358.22115)))
("SF_SOLAR" 0 ((15094.26889 7907.23982) (15091.70192 7918.55204) (15099.09514 7933.63495) (15168.63382 8035.44502)
(15177.22285 8058.06946)))
("SF_SOLAR" 0 ((15101.80995 7990.19615) (15098.03880 7982.65452)))
("SF_PLANTING" 0 ((15203.61991 912.51980) (15162.14219 901.20758) (15113.12217 901.36086) (15098.03880 912.51980)))
("SF_PLANTING" 0 ((15098.03880 912.51980) (15109.35102 950.22624)))
("SF_SOLAR" 0 ((15105.58111 8133.48416) (15105.58111 8122.17195) (15101.80995 8118.40113)))
("SF_PLANTING" 0 ((15120.66324 343.13631) (15101.80995 358.22115)))
("SF_PLANTING" 0 ((15109.35102 388.38518) (15101.80995 358.22115)))
("SF_PLANTING" 0 ((15109.35102 233.78676) (15109.20317 252.63857) (15101.80995 275.26301)))
("SF_PLANTING" 0 ((15101.80995 275.26301) (15105.43337 282.81233) (15105.58111 305.42986)))
("SF_PLANTING" 0 ((15103.69491 1008.67364) (15116.89333 1006.78733)))
("SF_PLANTING" 0 ((15103.69491 1008.67364) (15105.58111 972.85068)))
("SF_PLANTING" 0 ((15116.89333 1063.34842) (15102.86629 1025.64197) (15103.69491 1008.67364)))
("SF_PLANTING" 0 ((15105.58111 3416.28959) (15109.35102 3427.60181)))
("SF_MASONRY_AND_ARCH" 0 ((15105.58111 3239.06482) (15105.72896 3174.96256) (15109.35102 3156.10860) (15105.58111
2960.03043)))
("SF_PLANTING" 0 ((15105.58111 3239.06482) (15135.74661 3242.82274) (15147.05882 3239.06459)))
("SF_MASONRY_AND_ARCH" 0 ((15147.05882 2960.03043) (15105.58111 2960.03043)))
("SF_PLANTING" 0 ((15105.58111 972.85068) (15109.35102 950.22624)))
("SF_PLANTING" 0 ((15116.89333 305.42986) (15105.58111 305.42986)))
("SF_PLANTING" 0 ((15169.68326 972.85068) (15158.36414 957.91572) (15147.05882 951.28258) (15131.97545 947.65362)
(15109.35102 950.22624)))
("SF_PLANTING" 0 ((15109.35102 233.78676) (15169.68326 233.93382) (15188.53507 237.55656)))
("SF_PLANTING" 0 ((15116.89333 305.42986) (15135.74661 297.88744)))
("SF_PLANTING" 0 ((15120.66324 343.13631) (15116.89333 305.42986)))
("SF_SOLAR" 0 ((15120.66324 8069.38167) (15124.43439 8080.69389)))
("SF_SOLAR" 0 ((15131.97545 7937.40577) (15120.66324 7937.40577)))
("SF_ARCHITECTURE" 0 ((15120.66324 5143.28767) (15124.43439 5147.05882) (15131.97545 5143.28767)))
("SF_MASONRY_AND_ARCH" 0 ((15120.66324 2575.41505) (15128.20554 2575.41505)))
("SF_PLANTING" 0 ((15120.66324 343.13631) (15153.40950 384.61538) (15162.14219 414.78224)))
("SF_SOLAR" 0 ((15128.20554 8035.44502) (15124.43439 8016.59118)))
("SF_PLANTING" 0 ((15131.97545 3514.32907) (15124.43439 3506.78733)))
("SF_PLANTING" 0 ((15158.37104 3469.08020) (15128.36029 3464.11109) (15124.43439 3457.76799)))
("SF_MASONRY_AND_ARCH" 0 ((15124.43439 2530.16618) (15124.43439 2552.79061)))
("SF_MASONRY_AND_ARCH" 0 ((15124.43439 2530.16618) (15177.22285 2530.01844) (15196.08032 2526.39491) (15305.42986
2530.15995) (15331.82692 2526.39491)))
("SF_PLANTING" 0 ((15131.97545 4008.29604) (15128.20554 4015.83710)))
("SF_PLANTING" 0 ((15162.14219 414.78224) (15128.20554 426.09446)))
("SF_PLANTING" 0 ((15128.20554 426.09446) (15135.74661 448.71889)))
("SF_PLANTING" 0 ((15154.59989 4049.77376) (15139.51776 4050.97828) (15132.13009 4057.32172) (15128.50803 4064.85645)
(15131.97545 4076.16934)))
("SF_PLANTING" 0 ((15131.97545 4008.29604) (15131.97545 3993.21267)))
("SF_PLANTING" 0 ((15131.97545 4008.29604) (15149.62590 4015.98518) (15154.59989 4049.77376)))
("SF_PLANTING" 0 ((15131.97545 3993.21267) (15145.64615 3975.19457) (15143.43541 3959.27602) (15150.98473 3929.11052)
(15165.91210 3898.94378)))
("SF_PLANTING" 0 ((15131.97545 3514.32907) (15165.91210 3514.32907)))
("SF_PLANTING" 0 ((15165.91210 3536.95351) (15139.67251 3539.51980) (15131.97545 3514.32907)))
("SF_SOLAR" 0 ((15135.74661 7918.55204) (15155.65622 7960.03009) (15169.68326 7971.34231)))
("SF_PLANTING" 0 ((15169.68326 4072.39819) (15135.74661 4144.04265)))
("SF_PLANTING" 0 ((15135.74661 3789.59276) (15135.74661 3804.67613)))
("SF_PLANTING" 0 ((15135.74661 3804.67613) (15145.86165 3815.98835) (15150.82998 3834.84163)))
("SF_PLANTING" 0 ((15135.74661 3789.59276) (15162.14219 3785.82161)))
("SF_PLANTING" 0 ((15135.74661 3657.61731) (15143.14672 3655.19808) (15150.82998 3668.92952)))
("SF_PLANTING" 0 ((15188.53507 3585.97285) (15150.82998 3596.08088) (15135.74661 3585.97285)))
("SF_ARCHITECTURE" 0 ((15361.99095 5049.02002) (15162.14219 5130.78473) (15139.51776 5135.74661)))
("SF_PLANTING" 0 ((15158.37104 1067.11821) (15139.51776 1033.18156)))
("SF_PLANTING" 0 ((15169.68326 418.55204) (15171.20090 460.03111) (15144.34400 482.65554) (15139.66561 493.96776)
(15139.51776 520.36199)))
("SF_SOLAR" 0 ((15147.05882 8133.48416) (15143.28767 8129.71335) (15143.28767 8118.40113)))
("SF_PLANTING" 0 ((15150.82998 3834.84163) (15147.20656 3846.15385) (15147.05882 3880.09050)))
("SF_PLANTING" 0 ((15165.91210 3898.94378) (15158.22330 3884.01561) (15147.05882 3880.09050)))
("SF_PLANTING" 0 ((15188.53507 3736.80283) (15147.05882 3740.57274)))
("SF_PLANTING" 0 ((15158.37104 3438.91403) (15147.05882 3408.74785)))
("SF_MASONRY_AND_ARCH" 0 ((15147.05882 2960.03043) (15147.05882 3239.06459)))
("SF_PLANTING" 0 ((15180.99548 3239.06459) (15165.91210 3242.83586) (15147.05882 3239.06459)))
("SF_MASONRY_AND_ARCH" 0 ((15147.05882 2960.03043) (15180.99548 2960.03043)))
("SF_PLANTING" 0 ((15150.82998 3834.84163) (15188.53507 3834.84163)))
("SF_SOLAR" 0 ((15154.59989 7937.40577) (15373.30317 7937.40577)))
("SF_PLANTING" 0 ((15154.59989 4049.77376) (15169.68326 4072.39819)))
("SF_PLANTING" 0 ((15188.53507 3706.63609) (15173.45588 3699.24966) (15158.73971 3698.72636) (15158.37104 3687.78281)))
("SF_PLANTING" 0 ((15162.14219 3785.82161) (15188.53507 3744.34389)))
("SF_PLANTING" 0 ((15196.08032 3827.30057) (15184.61753 3804.68235) (15162.14219 3785.82161)))
("SF_PLANTING" 0 ((15162.14219 414.78224) (15169.68326 418.55204)))
("SF_SOLAR" 0 ((15165.91210 8009.04977) (15173.45588 8001.50837)))
("SF_ARCHITECTURE" 0 ((15199.84729 4966.06335) (15173.45995 4966.21143) (15165.91210 4969.83450)))
("SF_ARCHITECTURE" 0 ((15165.91210 4969.83450) (15165.91210 4981.14672) (15169.68326 4984.91663)))
("SF_PLANTING" 0 ((15165.91210 3898.94378) (15184.76810 3899.09876) (15192.30079 3902.86957) (15211.15950 3940.42274)))
("SF_PLANTING" 0 ((15165.91210 3536.95351) (15165.91210 3514.32907)))
("SF_PLANTING" 0 ((15165.91210 3536.95351) (15182.04491 3570.73552) (15188.53507 3574.66063)))
("SF_PLANTING" 0 ((15165.91210 3514.32907) (15203.61991 3506.78733)))
("SF_SOLAR" 0 ((15169.68326 7971.34231) (15388.38801 7971.33575) (15399.70023 7967.57172)))
("SF_SOLAR" 0 ((15169.68326 7971.34231) (15174.51086 7986.42534) (15290.49559 8162.44570) (15542.98643 8163.64344)
(15558.07127 8159.87941)))
("SF_ARCHITECTURE" 0 ((15199.84729 4966.06335) (15188.53100 4983.71278) (15169.68326 4984.91663)))
("SF_PLANTING" 0 ((15202.86459 4066.36505) (15192.41957 4072.16131) (15169.68326 4072.39819)))
("SF_PLANTING" 0 ((15169.68326 1036.95419) (15166.20758 1029.40486) (15169.68326 1010.55713)))
("SF_PLANTING" 0 ((15169.68326 1010.55713) (15192.30769 995.47511)))
("SF_PLANTING" 0 ((15169.68326 972.85068) (15152.18880 991.70532) (15154.76143 999.24491) (15169.68326 1010.55713)))
("SF_PLANTING" 0 ((15169.68326 972.85068) (15184.76810 972.85068)))
("SF_PLANTING" 0 ((15203.61991 384.61538) (15202.41572 392.16267) (15192.30769 403.47002) (15169.68326 418.55204)))
("SF_SOLAR" 0 ((15173.45588 7926.09355) (15173.45588 7918.55204)))
("SF_SOLAR" 0 ((15177.22285 8058.06946) (15192.30769 8065.61086)))
("SF_SOLAR" 0 ((15196.08032 8133.48416) (15180.99548 8118.40113)))
("SF_PLANTING" 0 ((15188.53507 3355.95803) (15181.14321 3337.10407) (15180.99548 3318.25011)))
("SF_MASONRY_AND_ARCH" 0 ((15180.99548 3239.06459) (15180.99548 2960.03043)))
("SF_PLANTING" 0 ((15180.99548 3239.06459) (15196.08032 3242.83586) (15218.70475 3239.06459)))
("SF_MASONRY_AND_ARCH" 0 ((15180.99548 2960.03043) (15218.70475 2960.03043)))
("SF_PLANTING" 0 ((15184.76810 3442.68450) (15199.84729 3435.14355)))
("SF_PLANTING" 0 ((15184.76810 972.85068) (15193.50351 942.68382) (15207.39253 931.37161)))
("SF_PLANTING" 0 ((15184.76810 972.85068) (15192.30769 995.47511)))
("SF_SOLAR" 0 ((15188.53507 7948.71799) (15188.53507 7960.03020)))
("SF_PLANTING" 0 ((15196.08032 3827.30057) (15192.30769 3834.84163) (15188.53507 3834.84163)))
("SF_PLANTING" 0 ((15192.30769 3861.23722) (15188.53507 3834.84163)))
("SF_PLANTING" 0 ((15188.53507 3744.34389) (15188.53507 3736.80283)))
("SF_PLANTING" 0 ((15207.39253 3774.50939) (15198.79231 3755.65611) (15188.53507 3744.34389)))
("SF_PLANTING" 0 ((15188.53507 3736.80283) (15188.53507 3717.94830)))
("SF_PLANTING" 0 ((15248.86878 3717.94830) (15188.53507 3717.94830)))
("SF_PLANTING" 0 ((15188.53507 3706.63609) (15188.53507 3717.94830)))
("SF_PLANTING" 0 ((15192.30769 3661.38722) (15192.15995 3699.08880) (15188.53507 3706.63609)))
("SF_PLANTING" 0 ((15188.53507 3585.97285) (15188.53507 3574.66063)))
("SF_PLANTING" 0 ((15192.30769 3661.38722) (15184.91448 3646.30509) (15184.92138 3634.99287) (15192.15441 3619.90950)
(15188.53507 3585.97285)))
("SF_PLANTING" 0 ((15203.61991 3506.78733) (15211.01312 3521.87002) (15212.05577 3548.26572) (15203.47217 3566.97115)
(15188.53507 3574.66063)))
("SF_PLANTING" 0 ((15301.65724 248.86878) (15279.03281 233.94005) (15196.08439 233.93382) (15188.53507 237.55656)))
("SF_PLANTING" 0 ((15188.53507 237.55656) (15196.23360 263.95079) (15207.39253 274.20735) (15237.55656 290.34785)))
("SF_SOLAR" 0 ((15211.15950 8058.06946) (15192.30769 8065.61086)))
("SF_SOLAR" 0 ((15233.78394 8141.02557) (15197.12704 8080.69389) (15192.30769 8065.61086)))
("SF_PLANTING" 0 ((15192.30769 3661.38722) (15211.15543 3656.41256) (15218.70475 3642.53394)))
("SF_PLANTING" 0 ((15203.61991 3506.78733) (15202.42410 3484.16290) (15192.30769 3472.85068)))
("SF_PLANTING" 0 ((15246.98529 1059.57862) (15211.15950 1063.19378) (15192.30769 1052.03620)))
("SF_PLANTING" 0 ((15243.21267 999.24491) (15203.61991 999.09785) (15192.30769 995.47511)))
("SF_SOLAR" 0 ((15196.08032 7997.73756) (15411.01244 7997.73756)))
("SF_PLANTING" 0 ((15226.24434 3827.30057) (15196.08032 3827.30057)))
("SF_PLANTING" 0 ((15196.08032 3423.83133) (15199.84729 3435.14355)))
("SF_ARCHITECTURE" 0 ((15199.84729 4966.06335) (15207.38416 4943.43891) (15203.76765 4917.04333) (15202.86459
4066.36505)))
("SF_PLANTING" 0 ((15214.93213 3438.91403) (15199.84729 3435.14355)))
("SF_PLANTING" 0 ((15202.86459 4066.36505) (15196.34536 4060.99038) (15196.22670 4023.37817) (15203.47217 3981.90045)
(15203.76765 3955.50486) (15211.15950 3940.42274)))
("SF_MASONRY_AND_ARCH" 0 ((15203.61991 2126.69683) (15207.54581 2116.58880) (15226.24434 2115.38462)))
("SF_MASONRY_AND_ARCH" 0 ((15203.61991 2126.69683) (15211.15950 2134.23857)))
("SF_PLANTING" 0 ((15248.86878 901.20758) (15218.70475 902.26324) (15203.61991 912.51980)))
("SF_PLANTING" 0 ((15203.61991 912.51980) (15207.39253 931.37161)))
("SF_PLANTING" 0 ((15237.55656 309.19966) (15241.17998 316.74898) (15240.12364 339.36652) (15211.02149 380.69027)
(15203.61991 384.61538)))
("SF_PLANTING" 0 ((15237.55656 309.19966) (15207.39661 317.79842) (15189.72817 343.13631) (15184.91448 358.22115)
(15185.97081 376.91968) (15203.61991 384.61538)))
("SF_PLANTING" 0 ((15245.09615 946.45645) (15207.39253 931.37161)))
("SF_SOLAR" 0 ((15211.15950 7982.65452) (15211.15950 7990.19615)))
("SF_PLANTING" 0 ((15245.09615 3944.19265) (15211.15950 3940.42274)))
("SF_PLANTING" 0 ((15218.70475 3876.31934) (15256.40837 3887.63156)))
("SF_MASONRY_AND_ARCH" 0 ((15218.70475 3239.06459) (15218.70475 2960.03043)))
("SF_PLANTING" 0 ((15218.70475 3239.06459) (15237.55656 3242.83586) (15256.40837 3239.06459)))
("SF_MASONRY_AND_ARCH" 0 ((15256.40837 2960.03043) (15241.32919 2956.25916) (15218.70475 2960.03043)))
("SF_PLANTING" 0 ((15222.47172 3631.22172) (15229.86776 3608.59729) (15234.84174 3570.89016) (15256.40837 3525.64129)))
("SF_PLANTING" 0 ((15230.01697 456.25848) (15228.81833 467.56584) (15222.47172 475.11312)))
("SF_SOLAR" 0 ((15226.24434 8012.82059) (15275.26584 8014.49197) (15312.96946 8009.04977)))
("SF_ARCHITECTURE" 0 ((15226.24434 5720.21109) (15441.17647 5720.21109)))
("SF_PLANTING" 0 ((15226.24434 3827.30057) (15234.84174 3808.44672) (15248.86878 3797.13382)))
("SF_PLANTING" 0 ((15226.24434 3827.30057) (15237.55656 3841.32658) (15279.03281 3860.18676) (15331.82692 3868.77828)))
("SF_MASONRY_AND_ARCH" 0 ((15226.24434 2115.38462) (15230.17025 2105.12873) (15251.43586 2088.98971) (15252.49219
2073.91312) (15248.86878 2066.36527)))
("SF_MASONRY_AND_ARCH" 0 ((15226.24434 2115.38462) (15237.55656 2121.72839) (15252.64140 2122.92636)))
("SF_SOLAR" 0 ((15237.55656 8103.31833) (15230.01697 8107.08891)))
("SF_PLANTING" 0 ((15275.26584 361.99095) (15275.11663 403.47002) (15266.67387 429.86425) (15248.86878 451.29072)
(15230.01697 456.25848)))
("SF_PLANTING" 0 ((15275.26584 361.99095) (15260.18100 366.81787) (15246.29615 380.84559) (15230.01697 456.25848)))
("SF_SOLAR" 0 ((15233.78394 8141.02557) (15243.89344 8152.33122) (15245.09615 8159.87941)))
("SF_SOLAR" 0 ((15233.78394 8058.06946) (15456.26131 8058.07602) (15471.34050 8061.54400) (15486.42534 8058.06946)))
("SF_SOLAR" 0 ((15245.09615 8035.44502) (15241.32919 8027.90339) (15233.78394 8024.13281)))
("SF_PLANTING" 0 ((15237.55656 309.19966) (15237.55656 290.34785)))
("SF_PLANTING" 0 ((15296.00113 282.80543) (15248.86878 282.96007) (15237.55656 290.34785)))
("SF_SOLAR" 0 ((15241.32919 8133.48416) (15252.64140 8122.17195)))
("SF_SOLAR" 0 ((15241.32919 7960.03020) (15241.32919 7948.71799)))
("SF_PLANTING" 0 ((15243.21267 999.24491) (15279.03281 999.24491)))
("SF_PLANTING" 0 ((15243.21267 999.24491) (15245.09615 946.45645)))
("SF_PLANTING" 0 ((15243.21267 999.24491) (15248.72104 1036.95419) (15246.98529 1059.57862)))
("SF_SOLAR" 0 ((15245.09615 8159.87941) (15264.09163 8177.38077) (15271.49321 8174.96222)))
("SF_PLANTING" 0 ((15245.09615 4000.75373) (15256.40837 4004.52489)))
("SF_PLANTING" 0 ((15245.09615 3944.19265) (15260.18100 3933.03541) (15282.80543 3929.25837) (15301.65724 3930.99548)))
("SF_PLANTING" 0 ((15245.09615 3944.19265) (15256.40837 3966.81708)))
("SF_PLANTING" 0 ((15252.64140 942.68382) (15245.09615 946.45645)))
("SF_PLANTING" 0 ((15248.86878 1134.99152) (15241.32726 1131.06708) (15241.32726 1112.36708) (15241.32726 1074.66063)
(15246.98529 1059.57862)))
("SF_PLANTING" 0 ((15246.98529 1059.57862) (15297.89027 1063.34842)))
("SF_PLANTING" 0 ((15248.86878 3710.40724) (15248.86878 3717.94830)))
("SF_PLANTING" 0 ((15252.64140 3759.42726) (15249.01652 3751.87873) (15248.86878 3717.94830)))
("SF_PLANTING" 0 ((15294.11765 3687.78281) (15286.42195 3709.20271) (15248.86878 3710.40724)))
("SF_PLANTING" 0 ((15248.86878 3710.40724) (15241.47557 3699.09502) (15241.47557 3676.47059) (15246.14706 3661.38722)
(15256.41674 3647.36052) (15275.26584 3638.76278)))
("SF_MASONRY_AND_ARCH" 0 ((15248.86878 2066.36527) (15248.86878 1146.30373)))
("SF_PLANTING" 0 ((15297.88835 1144.42025) (15248.86878 1146.30373)))
("SF_PLANTING" 0 ((15248.86878 1134.99152) (15248.86878 1146.30373)))
("SF_PLANTING" 0 ((15248.86878 1134.99152) (15258.97681 1123.67930) (15260.18100 1097.28507)))
("SF_PLANTING" 0 ((15252.64140 942.68382) (15248.86878 901.20758)))
("SF_PLANTING" 0 ((15248.86878 901.20758) (15294.11765 902.26324) (15318.62557 918.17590)))
("SF_PLANTING" 0 ((15252.64140 3518.09955) (15256.40837 3525.64129)))
("SF_PLANTING" 0 ((15252.64140 3374.81120) (15256.40837 3393.66516)))
("SF_PLANTING" 0 ((15252.64140 942.68382) (15293.96437 948.87296) (15318.62557 918.17590)))
("SF_PLANTING" 0 ((15256.40837 4004.52489) (15256.40837 3966.81708)))
("SF_PLANTING" 0 ((15256.40837 4004.52489) (15260.18100 4015.83710)))
("SF_PLANTING" 0 ((15256.40837 3966.81708) (15301.65724 3974.35939)))
("SF_PLANTING" 0 ((15279.03281 3525.64129) (15256.40837 3525.64129)))
("SF_MASONRY_AND_ARCH" 0 ((15256.40837 2960.03043) (15256.40837 3239.06459)))
("SF_PLANTING" 0 ((15290.34502 3242.83586) (15263.95769 3242.68812) (15256.40837 3239.06459)))
("SF_MASONRY_AND_ARCH" 0 ((15256.40837 2960.03043) (15271.49321 2956.25916) (15290.34502 2960.03043)))
("SF_MASONRY_AND_ARCH" 0 ((15256.40837 2631.97590) (15256.40837 2658.37104)))
("SF_MASONRY_AND_ARCH" 0 ((15256.40837 2658.37104) (15263.95769 2665.91256) (15411.01244 2665.91256) (15433.63688
2665.91256) (15478.88575 2665.91256) (15542.98643 2658.37104)))
("SF_MASONRY_AND_ARCH" 0 ((15256.40837 2631.97590) (15267.72059 2631.97590) (15297.89027 2631.97590) (15316.74208
2631.97590) (15426.09163 2631.97590)))
("SF_SOLAR" 0 ((15260.18100 8099.54751) (15271.49321 8103.31833)))
("SF_PLANTING" 0 ((15354.45136 4049.77376) (15305.42986 4048.56923) (15282.79853 4024.43484) (15260.18100 4015.83710)))
("SF_MASONRY_AND_ARCH" 0 ((15463.80090 2560.33156) (15448.71606 2574.21086) (15429.86425 2579.03088) (15411.01244
2575.42127) (15365.76357 2579.18552) (15343.13914 2575.42127) (15263.95362 2575.41505)))
("SF_SOLAR" 0 ((15271.49321 8152.33778) (15267.72059 8159.87941)))
("SF_SOLAR" 0 ((15267.72059 8110.85973) (15271.49321 8103.31833)))
("SF_SOLAR" 0 ((15267.72059 8076.92308) (15267.72059 8069.38167)))
("SF_SOLAR" 0 ((15271.49321 8103.31833) (15346.90611 8103.17025) (15361.99095 8099.55419) (15384.61538 8103.16369)
(15418.55204 8097.87602) (15478.88575 8099.54751)))
("SF_PLANTING" 0 ((15279.03281 3616.13903) (15275.26584 3638.76278)))
("SF_PLANTING" 0 ((15294.11765 3687.78281) (15284.00962 3672.69943) (15282.65215 3650.07568) (15275.26584 3638.76278)))
("SF_PLANTING" 0 ((15275.26584 361.99095) (15287.63303 335.59672) (15297.89027 324.28450)))
("SF_PLANTING" 0 ((15279.03281 3616.13903) (15312.96946 3612.36776)))
("SF_PLANTING" 0 ((15279.03281 3525.64129) (15279.78133 3555.80667) (15265.15633 3574.66063) (15263.95362 3585.97285)
(15266.82715 3601.05554) (15279.03281 3616.13903)))
("SF_PLANTING" 0 ((15279.03281 3525.64129) (15286.42885 3506.78733) (15287.63303 3487.93337) (15294.11765 3476.62115)))
("SF_PLANTING" 0 ((15282.80543 991.70532) (15279.03281 999.24491)))
("SF_PLANTING" 0 ((15305.42986 1021.86934) (15297.73971 1011.60735) (15279.03281 999.24491)))
("SF_SOLAR" 0 ((15282.80543 8024.13281) (15286.57805 8039.21561)))
("SF_MASONRY_AND_ARCH" 0 ((15305.42986 2224.73631) (15282.80543 2228.50679)))
("SF_PLANTING" 0 ((15282.80543 512.81957) (15286.73133 514.34412) (15300.60226 505.13156) (15305.42986 478.88292)))
("SF_PLANTING" 0 ((15305.42986 478.88292) (15286.57805 475.11312)))
("SF_SOLAR" 0 ((15509.04977 8141.02557) (15305.42986 8141.03213) (15290.34502 8144.79638)))
("SF_SOLAR" 0 ((15290.34502 7948.71799) (15290.34502 7952.48869) (15297.89027 7956.25939)))
("SF_PLANTING" 0 ((15290.34502 3242.83586) (15320.50633 3242.68812) (15328.05430 3239.06459)))
("SF_MASONRY_AND_ARCH" 0 ((15290.34502 3242.83586) (15290.34502 2960.03043)))
("SF_MASONRY_AND_ARCH" 0 ((15328.05430 2960.03043) (15309.20249 2956.25916) (15290.34502 2960.03043)))
("SF_PLANTING" 0 ((15294.11765 3687.78281) (15320.51471 3688.83258) (15350.67873 3702.86618)))
("SF_PLANTING" 0 ((15296.00113 282.80543) (15301.50543 271.49321) (15301.65724 248.86878)))
("SF_PLANTING" 0 ((15296.00113 282.80543) (15297.89027 324.28450)))
("SF_PLANTING" 0 ((15296.00113 282.80543) (15335.59389 287.63235) (15358.21425 304.22500) (15365.76357 305.42986)))
("SF_MASONRY_AND_ARCH" 0 ((15297.88835 2100.30192) (15297.88835 1172.70079)))
("SF_PLANTING" 0 ((15297.88835 1144.42025) (15297.88835 1172.70079)))
("SF_PLANTING" 0 ((15335.59389 1184.01301) (15328.04740 1177.66855) (15297.88835 1172.70079)))
("SF_PLANTING" 0 ((15297.88835 1144.42025) (15320.51471 1137.70701) (15331.82692 1123.67930)))
("SF_PLANTING" 0 ((15297.88835 1144.42025) (15297.89027 1063.34842)))
("SF_SOLAR" 0 ((15297.89027 8182.50385) (15297.89027 8174.96222)))
("SF_SOLAR" 0 ((15301.65724 8133.48416) (15297.89027 8122.17195)))
("SF_SOLAR" 0 ((15358.21833 7858.22025) (15346.90611 7854.59751) (15308.90000 7854.15339) (15297.89027 7865.76165)))
("SF_SOLAR" 0 ((15297.89027 7865.76165) (15305.42986 7888.38609)))
("SF_PLANTING" 0 ((15305.42986 1021.86934) (15305.28213 1040.72398) (15297.89027 1063.34842)))
("SF_PLANTING" 0 ((15316.74208 335.59672) (15297.89027 324.28450)))
("SF_PLANTING" 0 ((15301.65724 3930.99548) (15305.42986 3951.73495) (15301.65724 3974.35939)))
("SF_PLANTING" 0 ((15358.21833 4012.06595) (15335.59389 4011.91810) (15316.88982 4003.46821) (15306.47930 3989.44152)
(15301.65724 3974.35939)))
("SF_PLANTING" 0 ((15328.05430 3902.71493) (15316.88982 3910.26290) (15301.65724 3930.99548)))
("SF_PLANTING" 0 ((15301.65724 3930.99548) (15346.90611 3936.65158)))
("SF_PLANTING" 0 ((15301.65724 248.86878) (15312.96946 238.75452) (15328.05430 233.93382) (15369.53054 237.55656)))
("SF_MASONRY_AND_ARCH" 0 ((15305.42986 2224.73631) (15312.97783 2216.29977) (15373.30317 2190.79966)))
("SF_MASONRY_AND_ARCH" 0 ((15309.20249 2239.81900) (15305.42986 2224.73631)))
("SF_PLANTING" 0 ((15305.42986 1021.86934) (15354.44299 1018.24729) (15361.99095 1021.86934)))
("SF_PLANTING" 0 ((15305.42986 478.88292) (15309.05328 467.57070) (15313.11867 377.08054) (15316.74208 369.53337)))
("SF_SOLAR" 0 ((15309.20249 8069.38167) (15309.20249 8084.46448)))
("SF_SOLAR" 0 ((15324.28167 8042.98643) (15317.78462 8039.06097) (15309.20249 8020.36199)))
("SF_SOLAR" 0 ((15309.20249 7986.42534) (15309.20249 7978.88394)))
("SF_SOLAR" 0 ((15309.20249 7918.55204) (15309.20249 7926.09355)))
("SF_MASONRY_AND_ARCH" 0 ((15309.20249 2239.81900) (15331.82692 2234.99208) (15361.99095 2221.86063) (15377.07579
2205.88235)))
("SF_PLANTING" 0 ((15312.96946 3612.36776) (15320.51878 3602.25973) (15339.36652 3597.28507)))
("SF_PLANTING" 0 ((15312.96946 3612.36776) (15324.28167 3622.48281) (15346.90611 3627.45057)))
("SF_MASONRY_AND_ARCH" 0 ((15312.96946 2386.87783) (15369.53054 2383.25509) (15426.09163 2394.41957)))
("SF_PLANTING" 0 ((15316.74208 3774.50939) (15317.94627 3766.96210) (15349.62240 3717.94830) (15350.67873 3702.86618)))
("SF_PLANTING" 0 ((15343.13914 369.53337) (15316.74208 369.53337)))
("SF_PLANTING" 0 ((15316.74208 335.59672) (15316.74208 369.53337)))
("SF_PLANTING" 0 ((15343.13914 350.67873) (15335.58982 340.57138) (15316.74208 335.59672)))
("SF_PLANTING" 0 ((15380.84276 904.97738) (15335.59389 905.13201) (15318.62557 918.17590)))
("SF_PLANTING" 0 ((15318.62557 918.17590) (15350.68563 957.76109) (15373.14989 972.99910) (15380.84276 987.93269)))
("SF_PLANTING" 0 ((15395.92760 3812.21719) (15380.84276 3804.83009) (15350.67873 3804.52771) (15320.51471 3797.13382)))
("SF_PLANTING" 0 ((15365.76357 1112.36708) (15339.51425 1111.16369) (15324.28167 1089.74265)))
("SF_PLANTING" 0 ((15328.05430 3902.71493) (15331.82692 3868.77828)))
("SF_PLANTING" 0 ((15328.05430 3902.71493) (15338.17070 3914.02715) (15346.90611 3936.65158)))
("SF_PLANTING" 0 ((15328.05430 3239.06459) (15365.76357 3239.06459)))
("SF_MASONRY_AND_ARCH" 0 ((15328.05430 2960.03043) (15328.05430 3239.06459)))
("SF_MASONRY_AND_ARCH" 0 ((15328.05430 2960.03043) (15365.76357 2960.03043)))
("SF_SOLAR" 0 ((15331.82692 8133.48416) (15331.82692 8118.40113)))
("SF_SOLAR" 0 ((15331.82692 8069.38167) (15339.36652 8080.69389)))
("SF_SOLAR" 0 ((15331.82692 7986.42534) (15331.82692 7978.88394)))
("SF_SOLAR" 0 ((15331.82692 7960.03020) (15331.82692 7948.71799)))
("SF_PLANTING" 0 ((15331.82692 3868.77828) (15354.45136 3865.00713)))
("SF_SOLAR" 0 ((15358.21833 8042.98643) (15339.36652 8012.82059)))
("SF_PLANTING" 0 ((15339.36652 3597.28507) (15340.57070 3578.43801) (15354.45136 3570.89016)))
("SF_PLANTING" 0 ((15350.67873 3619.90950) (15339.36652 3597.28507)))
("SF_SOLAR" 0 ((15343.13914 7926.09355) (15343.13914 7914.78133)))
("SF_PLANTING" 0 ((15343.13914 369.53337) (15343.13914 414.78224)))
("SF_PLANTING" 0 ((15350.67873 448.71889) (15343.28552 429.86425) (15343.13914 414.78224)))
("SF_PLANTING" 0 ((15403.46719 448.71889) (15380.99887 429.86425) (15373.14989 415.98563) (15343.13914 414.78224)))
("SF_PLANTING" 0 ((15373.30317 369.53337) (15343.13914 369.53337)))
("SF_PLANTING" 0 ((15343.13914 350.67873) (15343.13914 369.53337)))
("SF_PLANTING" 0 ((15343.13914 350.67873) (15358.21833 350.67873)))
("SF_PLANTING" 0 ((15354.45136 3944.19265) (15350.67873 3944.19265) (15346.90611 3936.65158)))
("SF_PLANTING" 0 ((15350.67873 3619.90950) (15346.90611 3627.45057)))
("SF_PLANTING" 0 ((15365.76357 3695.32387) (15354.59774 3665.15837) (15346.90611 3627.45057)))
("SF_MASONRY_AND_ARCH" 0 ((15346.90611 2526.39491) (15388.38801 2530.16618) (15460.02828 2526.39491)))
("SF_PLANTING" 0 ((15365.76357 3695.32387) (15350.67873 3702.86618)))
("SF_PLANTING" 0 ((15350.67873 3619.90950) (15369.53054 3620.96618) (15395.92760 3637.56550) (15426.09163 3649.01957)
(15452.48869 3653.83993) (15471.34050 3650.07500)))
("SF_SOLAR" 0 ((15429.86425 8012.82059) (15354.45136 8016.59118)))
("SF_SOLAR" 0 ((15354.45136 7948.71799) (15358.21833 7956.25939)))
("SF_PLANTING" 0 ((15354.45136 4049.77376) (15358.21833 4038.46154)))
("SF_ARCHITECTURE" 0 ((15354.45136 4049.77376) (15354.59774 4136.50034) (15361.98405 4159.12477) (15361.99095
5049.02002)))
("SF_PLANTING" 0 ((15354.45136 3944.19265) (15369.53054 3940.42274)))
("SF_PLANTING" 0 ((15361.99095 3993.21267) (15354.59774 3970.58824) (15354.45136 3944.19265)))
("SF_PLANTING" 0 ((15354.45136 3865.00713) (15365.90995 3842.53767) (15380.84276 3834.68699) (15395.92760 3819.75826)))
("SF_PLANTING" 0 ((15354.45136 3865.00713) (15377.07579 3880.09050)))
("SF_PLANTING" 0 ((15392.15498 3540.72398) (15373.30317 3530.62285) (15365.76765 3533.34389) (15355.49808 3552.03620)
(15354.45136 3570.89016)))
("SF_PLANTING" 0 ((15407.23982 3578.43111) (15354.45136 3570.89016)))
("SF_PLANTING" 0 ((15361.99095 1063.34842) (15354.45136 1070.89084)))
("SF_SOLAR" 0 ((15569.38348 7850.67873) (15554.29864 7854.44287) (15369.53054 7851.88303) (15358.21833 7858.22025)))
("SF_SOLAR" 0 ((15358.21833 7858.22025) (15377.07579 7892.15690)))
("SF_PLANTING" 0 ((15358.21833 4038.46154) (15358.21833 4012.06595)))
("SF_PLANTING" 0 ((15426.09163 4015.83710) (15403.46312 4041.02794) (15358.21833 4038.46154)))
("SF_PLANTING" 0 ((15361.99095 3993.21267) (15358.21833 4012.06595)))
("SF_SOLAR" 0 ((15361.99095 8118.40113) (15361.99095 8129.71335)))
("SF_ARCHITECTURE" 0 ((15365.76357 5090.49774) (15365.61437 5056.56731) (15361.99095 5049.02002)))
("SF_PLANTING" 0 ((15361.99095 3993.21267) (15426.09163 3996.98382)))
("SF_PLANTING" 0 ((15361.99095 1063.34842) (15361.99095 1021.86934)))
("SF_PLANTING" 0 ((15361.99095 1063.34842) (15380.84276 1074.66063)))
("SF_PLANTING" 0 ((15380.84276 987.93269) (15361.99095 1021.86934)))
("SF_ARCHITECTURE" 0 ((15365.76357 5090.49774) (15365.76357 5527.90351)))
("SF_ARCHITECTURE" 0 ((15365.76357 5527.90351) (15414.77941 5535.29695) (15433.63688 5527.90351)))
("SF_PLANTING" 0 ((15392.15498 3733.03167) (15379.78778 3710.40724) (15365.76357 3695.32387)))
("SF_MASONRY_AND_ARCH" 0 ((15365.76357 2960.03043) (15361.99095 3012.82025) (15365.76357 3239.06459)))
("SF_PLANTING" 0 ((15399.70023 3239.06459) (15380.84276 3242.83586) (15365.76357 3239.06459)))
("SF_MASONRY_AND_ARCH" 0 ((15395.92760 2960.03043) (15365.76357 2960.03043)))
("SF_PLANTING" 0 ((15365.76357 1112.36708) (15369.68665 1101.06244) (15380.84276 1093.51527)))
("SF_PLANTING" 0 ((15365.76357 1112.36708) (15365.90995 1161.38857) (15369.53054 1176.47059)))
("SF_PLANTING" 0 ((15452.48869 279.03563) (15399.70023 291.54502) (15384.61538 300.60294) (15365.76357 305.42986)))
("SF_PLANTING" 0 ((15369.53054 320.51188) (15365.76357 316.74208) (15365.76357 305.42986)))
("SF_MASONRY_AND_ARCH" 0 ((15369.53054 2141.77952) (15369.53054 1176.47059)))
("SF_MASONRY_AND_ARCH" 0 ((15369.53054 2141.77952) (15373.15543 2149.32817) (15373.30317 2190.79966)))
("SF_PLANTING" 0 ((15411.01244 1172.70079) (15369.53054 1176.47059)))
("SF_PLANTING" 0 ((15369.53054 237.55656) (15384.61538 233.78676) (15437.40385 233.93382) (15452.48869 237.55656)))
("SF_PLANTING" 0 ((15369.53054 237.55656) (15373.30317 263.95079)))
("SF_MASONRY_AND_ARCH" 0 ((15377.07579 2205.88235) (15373.30317 2190.79966)))
("SF_PLANTING" 0 ((15373.30317 369.53337) (15373.45645 350.67873) (15377.22907 343.29163) (15418.55204 327.00486)
(15463.80090 290.34785)))
("SF_PLANTING" 0 ((15373.30317 369.53337) (15380.85113 373.15543) (15407.23982 373.14853) (15433.63688 358.22115)))
("SF_SOLAR" 0 ((15377.07579 7978.88394) (15377.07579 7986.42534)))
("SF_SOLAR" 0 ((15392.15498 7937.40577) (15378.27161 7929.86425) (15377.07579 7914.78133)))
("SF_MASONRY_AND_ARCH" 0 ((15377.07579 2205.88235) (15395.92760 2204.82602) (15411.01052 2194.57014)))
("SF_SOLAR" 0 ((15380.84276 8073.15226) (15384.61538 8084.46448)))
("SF_PLANTING" 0 ((15380.84276 1093.51527) (15380.84276 1074.66063)))
("SF_PLANTING" 0 ((15380.84276 1093.51527) (15411.01244 1107.54785) (15452.48869 1116.13971)))
("SF_PLANTING" 0 ((15429.86425 1033.18156) (15418.55204 1048.11799) (15380.84276 1074.66063)))
("SF_PLANTING" 0 ((15422.32466 1003.01753) (15380.84276 987.93269)))
("SF_PLANTING" 0 ((15380.84276 904.97738) (15403.46719 897.43495) (15429.86425 897.58337) (15460.02828 904.97738)))
("SF_PLANTING" 0 ((15380.84276 904.97738) (15392.30554 930.32285) (15418.55204 945.40622) (15437.40385 950.22624)))
("SF_SOLAR" 0 ((15388.38801 8027.90339) (15399.70023 8042.98643)))
("SF_PLANTING" 0 ((15399.70023 3914.02715) (15394.73733 3925.18473) (15388.38801 3929.11052)))
("SF_SOLAR" 0 ((15429.86425 8114.63054) (15399.70430 8114.48247) (15392.15498 8110.85973)))
("SF_SOLAR" 0 ((15392.15498 7937.40577) (15411.01244 7937.40577)))
("SF_SOLAR" 0 ((15392.15498 7937.40577) (15399.70023 7967.57172)))
("SF_PLANTING" 0 ((15422.32466 3733.03167) (15392.15498 3733.03167)))
("SF_PLANTING" 0 ((15403.46719 3808.44604) (15392.30419 3770.73948) (15392.15498 3733.03167)))
("SF_PLANTING" 0 ((15395.92760 3812.21719) (15395.92760 3819.75826)))
("SF_PLANTING" 0 ((15437.40385 3902.71493) (15432.43133 3876.31934) (15419.60837 3861.23722) (15409.81244 3834.84163)
(15395.92760 3819.75826)))
("SF_PLANTING" 0 ((15403.46719 3808.44604) (15395.92760 3812.21719)))
("SF_MASONRY_AND_ARCH" 0 ((15395.92760 2960.03043) (15433.63688 2960.03043)))
("SF_MASONRY_AND_ARCH" 0 ((15399.70023 3239.06459) (15396.22308 3190.04525) (15399.69186 3174.96256) (15399.69186
3020.36199) (15396.22308 3005.27930) (15399.69186 2978.88360) (15395.92760 2960.03043)))
("SF_SOLAR" 0 ((15429.86425 8012.82059) (15417.49570 7986.42534) (15399.70023 7967.57172)))
("SF_PLANTING" 0 ((15399.70023 3239.06459) (15418.55204 3242.83586) (15433.63688 3239.06459)))
("SF_SOLAR" 0 ((15403.46719 7884.61538) (15403.46719 7892.15690)))
("SF_PLANTING" 0 ((15414.77941 3947.96380) (15403.46719 3947.96380)))
("SF_PLANTING" 0 ((15403.46719 3808.44604) (15422.32466 3812.06912) (15490.19796 3812.21719)))
("SF_PLANTING" 0 ((15403.46719 448.71889) (15455.06131 377.07296) (15468.62851 320.51188) (15478.88575 305.42986)))
("SF_PLANTING" 0 ((15403.46719 448.71889) (15407.23982 460.03111)))
("SF_PLANTING" 0 ((15407.23982 4102.56369) (15407.53529 4091.25147) (15432.57907 4061.08597) (15444.94910 4030.92048)))
("SF_PLANTING" 0 ((15407.23982 3578.43111) (15414.77941 3574.66063)))
("SF_PLANTING" 0 ((15407.23982 3578.43111) (15414.77941 3582.20238)))
("SF_MASONRY_AND_ARCH" 0 ((15411.01052 2194.57014) (15433.62851 2193.36595) (15444.94717 2183.25792) (15444.94717
2168.17523) (15426.09163 2153.09174)))
("SF_MASONRY_AND_ARCH" 0 ((15411.01052 2194.57014) (15411.01052 2168.17523) (15426.09163 2153.09174)))
("SF_SOLAR" 0 ((15422.32466 8084.46448) (15411.01244 8069.38167)))
("SF_SOLAR" 0 ((15448.71606 7971.34231) (15434.69186 7960.03009) (15411.01244 7914.78133)))
("SF_PLANTING" 0 ((15414.77941 3574.66063) (15411.01244 3563.34842)))
("SF_PLANTING" 0 ((15437.40385 1157.61595) (15414.93552 1162.58575) (15411.01244 1172.70079)))
("SF_PLANTING" 0 ((15411.01244 1172.70079) (15411.01052 1199.09502) (15426.09163 1210.40724)))
("SF_PLANTING" 0 ((15414.77941 3947.96380) (15433.63688 3947.96380)))
("SF_PLANTING" 0 ((15414.77941 3947.96380) (15415.83722 3978.12930) (15426.09163 3989.44152)))
("SF_PLANTING" 0 ((15414.77941 3574.66063) (15414.77941 3582.20238)))
("SF_PLANTING" 0 ((15471.34050 3638.76278) (15444.94910 3617.19536) (15422.47104 3607.54095) (15415.83722 3597.28507)
(15414.77941 3582.20238)))
("SF_PLANTING" 0 ((15414.77941 3574.66063) (15478.88575 3593.51459)))
("SF_SOLAR" 0 ((15422.32466 8035.44502) (15418.55204 8042.98643)))
("SF_PLANTING" 0 ((15422.32466 3733.03167) (15423.52048 3721.87410) (15429.86425 3717.94830)))
("SF_PLANTING" 0 ((15486.42534 3774.50939) (15463.80090 3752.94163) (15422.32466 3733.03167)))
("SF_PLANTING" 0 ((15422.32466 1003.01753) (15429.86425 1033.18156)))
("SF_PLANTING" 0 ((15448.71606 1018.09955) (15441.02873 1007.98529) (15422.32466 1003.01753)))
("SF_PLANTING" 0 ((15422.32466 524.13179) (15433.63688 531.67421)))
("SF_PLANTING" 0 ((15426.09163 4015.83710) (15426.09163 3996.98382)))
("SF_PLANTING" 0 ((15444.94910 4030.92048) (15437.39977 4019.76222) (15426.09163 4015.83710)))
("SF_PLANTING" 0 ((15426.09163 3989.44152) (15426.09163 3996.98382)))
("SF_PLANTING" 0 ((15441.17647 3947.96380) (15439.97229 3974.35939) (15426.09163 3989.44152)))
("SF_MASONRY_AND_ARCH" 0 ((15426.09163 1210.40724) (15426.09163 2153.09174)))
("SF_PLANTING" 0 ((15437.40385 1157.61595) (15437.25057 1195.32523) (15426.09163 1210.40724)))
("SF_SOLAR" 0 ((15471.34050 8035.44502) (15452.63643 8041.63405) (15429.86425 8012.82059)))
("SF_PLANTING" 0 ((15448.71606 1018.09955) (15441.02873 1029.25713) (15429.86425 1033.18156)))
("SF_SOLAR" 0 ((15433.63688 7993.96674) (15441.17647 7982.65452)))
("SF_ARCHITECTURE" 0 ((15471.34050 4068.62704) (15452.48869 4095.02262) (15433.64095 4140.27149) (15433.63688
5527.90351)))
("SF_ARCHITECTURE" 0 ((15509.04977 5527.90305) (15486.42534 5535.44536) (15452.48869 5535.29695) (15433.63688
5527.90351)))
("SF_PLANTING" 0 ((15441.17647 3947.96380) (15433.63688 3947.96380)))
("SF_PLANTING" 0 ((15437.40385 3902.71493) (15433.78326 3914.02715) (15433.63688 3947.96380)))
("SF_PLANTING" 0 ((15463.80090 3239.06459) (15433.63688 3239.06459)))
("SF_MASONRY_AND_ARCH" 0 ((15433.63688 3239.06459) (15433.63688 2960.03043)))
("SF_MASONRY_AND_ARCH" 0 ((15433.63688 2960.03043) (15463.80090 2960.03043)))
("SF_PLANTING" 0 ((15433.63688 561.84106) (15433.63688 531.67421)))
("SF_PLANTING" 0 ((15776.77036 595.77771) (15768.17443 573.15814) (15761.68281 566.81572) (15731.52149 561.98812)
(15678.73303 565.60464) (15493.96493 565.61086) (15433.63688 561.84106)))
("SF_PLANTING" 0 ((15452.48869 527.90441) (15433.63688 531.67421)))
("SF_SOLAR" 0 ((15629.71154 7937.40577) (15437.40385 7937.40577)))
("SF_PLANTING" 0 ((15437.40385 3902.71493) (15460.02828 3902.71493)))
("SF_MASONRY_AND_ARCH" 0 ((15493.96493 2631.97590) (15437.40385 2631.97590)))
("SF_PLANTING" 0 ((15452.48869 1127.45192) (15437.40385 1157.61595)))
("SF_PLANTING" 0 ((15460.02828 912.51980) (15437.40385 950.22624)))
("SF_PLANTING" 0 ((15444.94910 965.30826) (15437.40385 950.22624)))
("SF_SOLAR" 0 ((15441.17647 8069.38167) (15444.94910 8084.46448)))
("SF_ARCHITECTURE" 0 ((15840.87670 5707.01357) (15671.19344 5701.35747) (15652.33597 5708.89231) (15452.48869
5710.10294) (15441.17647 5720.21109)))
("SF_ARCHITECTURE" 0 ((15840.87670 5723.98190) (15833.18507 5734.08993) (15463.80090 5735.28756) (15456.26131
5734.08959) (15441.17647 5720.21109)))
("SF_PLANTING" 0 ((15441.17647 3947.96380) (15478.88575 3947.96380)))
("SF_SOLAR" 0 ((15444.94910 8129.71335) (15444.94910 8122.17195)))
("SF_SOLAR" 0 ((15444.94910 8012.82059) (15452.48869 8001.50837)))
("SF_SOLAR" 0 ((15444.94910 7918.55204) (15448.71606 7929.86425)))
("SF_PLANTING" 0 ((15444.94910 4030.92048) (15493.96493 4015.83710)))
("SF_SOLAR" 0 ((15448.71606 7971.34231) (15652.33597 7971.34231)))
("SF_SOLAR" 0 ((15448.71606 7971.34231) (15472.39830 8020.36199) (15492.90995 8046.75724) (15525.32353 8103.31833)
(15561.83824 8148.56719)))
("SF_PLANTING" 0 ((15448.71606 1018.09955) (15516.58937 1018.09955)))
("SF_PLANTING" 0 ((15452.48869 1127.45192) (15452.48869 1116.13971)))
("SF_PLANTING" 0 ((15492.08145 1191.55260) (15493.81855 1157.61595) (15489.14016 1146.45215) (15452.48869 1127.45192)))
("SF_PLANTING" 0 ((15516.58937 1036.95419) (15490.34434 1063.34842) (15464.85724 1097.28507) (15458.83937 1112.21380)
(15452.48869 1116.13971)))
("SF_PLANTING" 0 ((15452.48869 279.03563) (15452.48869 237.55656)))
("SF_PLANTING" 0 ((15452.48869 279.03563) (15463.80090 290.34785)))
("SF_PLANTING" 0 ((15505.27715 248.86878) (15486.42534 237.71120) (15452.48869 237.55656)))
("SF_PLANTING" 0 ((15456.26131 3435.14355) (15471.34050 3435.14355)))
("SF_MASONRY_AND_ARCH" 0 ((15463.80090 2394.41957) (15456.26131 2394.41957)))
("SF_PLANTING" 0 ((15475.11312 3891.40271) (15460.02828 3902.71493)))
("SF_PLANTING" 0 ((15478.88575 3936.65158) (15472.39140 3932.72647) (15460.02828 3902.71493)))
("SF_PLANTING" 0 ((15460.02828 3484.16290) (15478.88575 3491.70464)))
("SF_MASONRY_AND_ARCH" 0 ((15460.02828 2439.66844) (15460.02828 2526.39491)))
("SF_MASONRY_AND_ARCH" 0 ((15463.80090 2560.33156) (15460.17749 2552.78371) (15460.02828 2526.39491)))
("SF_PLANTING" 0 ((15460.02828 912.51980) (15460.02828 904.97738)))
("SF_PLANTING" 0 ((15460.02828 912.51980) (15482.65271 938.91403)))
("SF_PLANTING" 0 ((15460.02828 904.97738) (15471.34050 901.35464) (15501.51018 901.36086) (15516.58937 908.74717)))
("SF_SOLAR" 0 ((15463.80090 7948.71799) (15467.57353 7960.03020)))
("SF_MASONRY_AND_ARCH" 0 ((15463.80090 3239.06459) (15467.57353 3178.73303) (15467.56516 3005.27930) (15463.80090
2960.03043)))
("SF_PLANTING" 0 ((15535.44683 3237.17975) (15493.96493 3242.82964) (15463.80090 3239.06459)))
("SF_MASONRY_AND_ARCH" 0 ((15512.82240 2960.03043) (15490.19796 2956.25916) (15463.80090 2960.03043)))
("SF_MASONRY_AND_ARCH" 0 ((15463.80090 2560.33156) (15475.11312 2564.08971) (15493.96493 2560.33778) (15799.39480
2560.17692) (15810.55373 2549.01934) (15810.70701 2488.68778)))
("SF_PLANTING" 0 ((15482.65271 938.91403) (15485.36346 953.99604) (15477.82794 969.08088) (15463.80090 984.16290)))
("SF_PLANTING" 0 ((15463.80090 290.34785) (15478.88575 290.34785)))
("SF_SOLAR" 0 ((15467.57353 8118.40113) (15467.57353 8129.71335)))
("SF_SOLAR" 0 ((15478.88575 8084.46448) (15467.57353 8069.38167)))
("SF_SOLAR" 0 ((15467.57353 7929.86425) (15467.57353 7918.55204)))
("SF_PLANTING" 0 ((15467.57353 3861.23722) (15474.95984 3872.54943) (15475.11312 3891.40271)))
("SF_PLANTING" 0 ((15471.34050 3435.14355) (15467.57353 3416.28959)))
("SF_PLANTING" 0 ((15471.34050 3638.76278) (15471.34050 3650.07500)))
("SF_PLANTING" 0 ((15478.88575 3653.84615) (15471.34050 3650.07500)))
("SF_PLANTING" 0 ((15471.34050 3638.76278) (15478.88575 3608.59729)))
("SF_PLANTING" 0 ((15471.34050 3435.14355) (15476.16946 3446.45577) (15492.76222 3465.30894) (15493.96493 3480.39242)))
("SF_PLANTING" 0 ((15471.34050 3435.14355) (15490.19796 3438.91403)))
("SF_SOLAR" 0 ((15475.11312 8001.50837) (15490.19796 8002.71256) (15509.04977 8012.81391) (15614.63235 8012.67251)
(15637.25679 8006.47670) (15674.96041 8009.04977)))
("SF_PLANTING" 0 ((15497.73756 3898.94378) (15475.11312 3891.40271)))
("SF_PLANTING" 0 ((15478.88575 3936.65158) (15478.88575 3947.96380)))
("SF_PLANTING" 0 ((15478.88575 3947.96380) (15482.80192 3985.67161) (15493.96493 4015.83710)))
("SF_PLANTING" 0 ((15478.88575 3947.96380) (15524.13462 3951.73495)))
("SF_PLANTING" 0 ((15478.88575 3936.65158) (15488.99242 3925.33937) (15491.39378 3914.18179) (15497.73756 3910.25600)))
("SF_PLANTING" 0 ((15526.01810 3618.02387) (15501.51018 3649.01889) (15478.88575 3653.84615)))
("SF_PLANTING" 0 ((15478.88575 3653.84615) (15482.80882 3684.01165) (15490.19796 3695.32387)))
("SF_PLANTING" 0 ((15478.88575 3593.51459) (15478.88575 3608.59729)))
("SF_PLANTING" 0 ((15526.01810 3618.02387) (15478.88575 3608.59729)))
("SF_PLANTING" 0 ((15478.88575 3593.51459) (15486.57862 3578.57964) (15476.31731 3548.26572) (15482.65271 3536.95351)))
("SF_PLANTING" 0 ((15493.96493 3480.39242) (15478.88575 3491.70464)))
("SF_PLANTING" 0 ((15482.65271 3536.95351) (15478.88575 3491.70464)))
("SF_MASONRY_AND_ARCH" 0 ((15490.19796 2183.25792) (15482.65271 2187.02839) (15478.88575 2194.57014)))
("SF_PLANTING" 0 ((15478.88575 290.34785) (15478.88575 305.42986)))
("SF_PLANTING" 0 ((15516.58937 354.44853) (15497.58428 324.28450) (15478.88575 305.42986)))
("SF_PLANTING" 0 ((15505.27715 263.95079) (15478.88575 290.34785)))
("SF_PLANTING" 0 ((15482.65271 3536.95351) (15493.96493 3540.72398)))
("SF_PLANTING" 0 ((15492.08145 1191.55260) (15482.65271 1187.78281)))
("SF_PLANTING" 0 ((15516.58937 916.28959) (15497.73756 934.08710) (15482.65271 938.91403)))
("SF_PLANTING" 0 ((15486.42534 3774.50939) (15497.58428 3763.19717) (15490.19796 3695.32387)))
("SF_PLANTING" 0 ((15486.42534 3774.50939) (15490.19796 3812.21719)))
("SF_PLANTING" 0 ((15512.82240 3374.81120) (15501.50181 3359.88314) (15486.42534 3352.18676)))
("SF_SOLAR" 0 ((15527.90158 8152.33778) (15490.19796 8103.31833)))
("SF_SOLAR" 0 ((15490.19796 8088.23529) (15497.73756 8076.92308)))
("SF_SOLAR" 0 ((15490.19796 7982.65452) (15490.19796 7990.19615)))
("SF_PLANTING" 0 ((15490.19796 3812.21719) (15509.04977 3812.21719)))
("SF_PLANTING" 0 ((15546.75905 3706.63609) (15512.82240 3695.47229) (15490.19796 3695.32387)))
("SF_MASONRY_AND_ARCH" 0 ((15490.19796 2183.25792) (15492.08145 1191.55260)))
("SF_MASONRY_AND_ARCH" 0 ((15490.19796 2183.25792) (15501.51018 2194.57014)))
("SF_PLANTING" 0 ((15492.08145 1191.55260) (15520.36199 1187.78281)))
("SF_PLANTING" 0 ((15512.82240 4023.37817) (15493.96493 4015.83710)))
("SF_PLANTING" 0 ((15531.67421 3514.32907) (15520.50973 3509.50147) (15505.13077 3487.94027) (15493.96493 3480.39242)))
("SF_PLANTING" 0 ((15497.73756 3898.94378) (15497.73756 3910.25600)))
("SF_PLANTING" 0 ((15497.73756 3910.25600) (15519.15781 3929.11052) (15524.13462 3951.73495)))
("SF_PLANTING" 0 ((15497.73756 3898.94378) (15516.58937 3880.09050)))
("SF_SOLAR" 0 ((15501.51018 8099.54751) (15512.82240 8095.77670)))
("SF_MASONRY_AND_ARCH" 0 ((15501.51018 3208.89921) (15516.58937 3163.65034)))
("SF_MASONRY_AND_ARCH" 0 ((15501.51018 2322.77500) (15561.83824 2316.43190) (15708.89706 2318.99830) (15720.20928
2315.23405)))
("SF_SOLAR" 0 ((15505.27715 7997.73756) (15607.08710 7997.73756)))
("SF_PLANTING" 0 ((15505.27715 4208.14480) (15516.58529 4200.59683) (15523.97851 4189.29152) (15522.92907 4162.89593)
(15509.04977 4147.81256)))
("SF_PLANTING" 0 ((15505.27715 4208.14480) (15494.12104 4196.83258) (15494.11414 4166.66708) (15501.64819 4151.73835)
(15509.04977 4147.81256)))
("SF_PLANTING" 0 ((15505.27715 4208.14480) (15505.42636 4283.40520) (15509.04977 4287.33032)))
("SF_PLANTING" 0 ((15505.27715 3559.57794) (15512.82647 3557.01086) (15520.21425 3560.63428) (15535.44683 3582.20238)))
("SF_PLANTING" 0 ((15505.27715 263.95079) (15505.27715 248.86878)))
("SF_PLANTING" 0 ((15505.27715 263.95079) (15561.83824 309.19966)))
("SF_PLANTING" 0 ((15561.83824 237.55656) (15531.67421 233.93450) (15505.27715 248.86878)))
("SF_SOLAR" 0 ((15701.35747 8039.21561) (15509.04977 8042.98643)))
("SF_ARCHITECTURE" 0 ((15509.04977 5527.90305) (15509.04977 4287.33032)))
("SF_ARCHITECTURE" 0 ((15576.92308 5531.67421) (15569.37511 5535.29695) (15527.90158 5535.29695) (15509.04977
5527.90305)))
("SF_PLANTING" 0 ((15558.07127 4257.16482) (15539.21380 4274.96143) (15509.04977 4287.33032)))
("SF_PLANTING" 0 ((15509.04977 4147.81256) (15509.04977 4132.73043)))
("SF_PLANTING" 0 ((15561.83824 4000.75373) (15560.79152 4023.37817) (15526.70577 4113.87590) (15509.04977 4132.73043)))
("SF_PLANTING" 0 ((15512.82240 4023.37817) (15508.00034 4049.77376) (15490.20204 4098.79378) (15491.40068 4117.64706)
(15509.04977 4132.73043)))
("SF_PLANTING" 0 ((15509.04977 3823.52941) (15509.04977 3812.21719)))
("SF_PLANTING" 0 ((15509.04977 3823.52941) (15509.19751 3846.15385) (15516.58937 3880.09050)))
("SF_PLANTING" 0 ((15509.04977 3823.52941) (15561.83824 3834.84163)))
("SF_PLANTING" 0 ((15546.75905 3706.63609) (15538.15882 3763.19717) (15530.48394 3782.05170) (15509.04977 3812.21719)))
("SF_MASONRY_AND_ARCH" 0 ((15678.73303 2394.41957) (15588.23529 2405.72489) (15516.59774 2401.81278) (15509.04977
2398.19005)))
("SF_SOLAR" 0 ((15708.89706 8061.84005) (15512.82240 8061.84005)))
("SF_SOLAR" 0 ((15516.58937 8031.67421) (15512.82240 8024.13281)))
("SF_PLANTING" 0 ((15554.29864 4000.75373) (15542.98643 4011.01052) (15512.82240 4023.37817)))
("SF_MASONRY_AND_ARCH" 0 ((15512.82240 2960.03043) (15542.98643 2960.03043)))
("SF_MASONRY_AND_ARCH" 0 ((15512.82240 2960.03043) (15509.05667 2997.73756) (15512.81403 3016.59152) (15512.96878
3152.33812) (15516.58937 3163.65034)))
("SF_MASONRY_AND_ARCH" 0 ((15512.82240 2530.16618) (15524.13462 2526.40181) (15546.75905 2530.15995) (15637.25679
2530.16618) (15663.64819 2526.39491) (15754.14593 2526.40113) (15765.45814 2530.16618)))
("SF_PLANTING" 0 ((15535.44683 3887.63156) (15516.58937 3880.09050)))
("SF_MASONRY_AND_ARCH" 0 ((15539.21380 3163.65034) (15516.58937 3163.65034)))
("SF_PLANTING" 0 ((15516.58937 1036.95419) (15516.58937 1018.09955)))
("SF_PLANTING" 0 ((15516.58937 1036.95419) (15526.70577 1048.26640) (15535.44683 1070.89084)))
("SF_PLANTING" 0 ((15535.44683 1006.78733) (15516.58937 1018.09955)))
("SF_PLANTING" 0 ((15516.58937 916.28959) (15516.58937 908.74717)))
("SF_PLANTING" 0 ((15516.58937 916.28959) (15523.98541 935.14423) (15529.10023 976.46719) (15535.44683 980.39310)))
("SF_PLANTING" 0 ((15603.32014 912.51980) (15573.15045 897.58337) (15546.75905 897.58337) (15516.58937 908.74717)))
("SF_PLANTING" 0 ((15516.58937 354.44853) (15550.52602 354.44853)))
("SF_PLANTING" 0 ((15516.58937 354.44853) (15514.01821 365.76075) (15523.98541 452.48869) (15521.56063 471.34333)
(15531.67421 493.96776)))
("SF_SOLAR" 0 ((15531.67421 8125.94276) (15524.13462 8133.48416)))
("SF_PLANTING" 0 ((15524.13462 3951.73495) (15539.36437 3970.43360) (15550.52602 3974.35939)))
("SF_PLANTING" 0 ((15526.01810 3618.02387) (15531.45882 3608.66493) (15535.44683 3582.20238)))
("SF_PLANTING" 0 ((15526.01810 3618.02387) (15558.07127 3634.99287)))
("SF_PLANTING" 0 ((15527.90158 516.59219) (15531.67421 493.96776)))
("SF_SOLAR" 0 ((15531.67421 8095.77670) (15561.83824 8103.31165) (15584.46267 8099.55407) (15618.39932 8103.31176)
(15701.35747 8103.31821) (15739.06674 8099.54751)))
("SF_PLANTING" 0 ((15539.21380 3499.24559) (15531.67421 3514.32907)))
("SF_PLANTING" 0 ((15531.67421 3514.32907) (15539.21380 3533.18224)))
("SF_PLANTING" 0 ((15535.44683 3237.17975) (15535.29762 3276.77251) (15528.19853 3295.61946) (15531.67421 3303.16742)))
("SF_PLANTING" 0 ((15531.67421 493.96776) (15542.98643 490.04186) (15561.83824 471.34333)))
("SF_SOLAR" 0 ((15535.44683 7982.65452) (15535.44683 7990.19615)))
("SF_SOLAR" 0 ((15535.44683 7948.71799) (15535.44683 7960.03020)))
("SF_SOLAR" 0 ((15535.44683 7918.55204) (15535.44683 7926.09355)))
("SF_PLANTING" 0 ((15535.44683 3887.63156) (15565.61086 3876.31934)))
("SF_PLANTING" 0 ((15569.38348 3944.19265) (15540.41244 3902.71493) (15535.44683 3887.63156)))
("SF_PLANTING" 0 ((15535.44683 3582.20238) (15557.92070 3569.83993) (15572.09548 3552.03620) (15584.31629 3521.87002)
(15585.66821 3484.16290) (15599.54751 3465.30894)))
("SF_MASONRY_AND_ARCH" 0 ((15535.44683 3237.17975) (15542.83869 3212.66968) (15542.83869 3174.96256) (15539.21380
3163.65034)))
("SF_PLANTING" 0 ((15535.44683 3237.17975) (15576.91618 3238.91686) (15584.46267 3235.29412)))
("SF_PLANTING" 0 ((15558.06934 1155.73247) (15535.44683 1157.61595)))
("SF_PLANTING" 0 ((15535.44683 1070.89084) (15529.10023 1078.43801) (15520.36889 1108.59729) (15525.18133 1138.76414)
(15535.44683 1157.61595)))
("SF_MASONRY_AND_ARCH" 0 ((15558.06934 1155.73247) (15558.06934 1180.24038) (15558.06934 2187.02839) (15558.06934
2197.13654) (15539.36991 2198.63688) (15535.60011 2194.86629) (15531.82195 2149.32127) (15531.66731 1983.40848)
(15527.90995 1964.55532) (15531.67421 1753.39367) (15531.67421 1734.53903) (15531.67421 1195.32523) (15535.44683
1157.61595)))
("SF_PLANTING" 0 ((15535.44683 1070.89084) (15550.52602 1070.89084)))
("SF_PLANTING" 0 ((15535.44683 1006.78733) (15535.44683 980.39310)))
("SF_PLANTING" 0 ((15535.44683 1006.78733) (15542.99333 1010.41007) (15569.38348 1010.55713)))
("SF_PLANTING" 0 ((15565.61086 972.85068) (15546.75905 973.00532) (15535.44683 980.39310)))
("SF_PLANTING" 0 ((15539.21380 3469.08020) (15539.36301 3412.51912) (15546.75905 3382.35294)))
("SF_MASONRY_AND_ARCH" 0 ((15542.98643 2960.03043) (15542.99333 3118.40147) (15546.74525 3137.25464) (15539.21380
3163.65034)))
("SF_MASONRY_AND_ARCH" 0 ((15542.98643 2658.37104) (15539.21380 2639.51708)))
("SF_SOLAR" 0 ((15542.98643 8073.15226) (15546.75905 8073.15226) (15554.29864 8084.46448)))
("SF_MASONRY_AND_ARCH" 0 ((15542.98643 2960.03043) (15584.46267 2960.03043)))
("SF_MASONRY_AND_ARCH" 0 ((15542.98643 2658.37104) (15561.83824 2665.91256) (15652.33597 2665.90656) (15686.27262
2662.14152)))
("SF_ARCHITECTURE" 0 ((15546.75713 7567.87330) (15546.75713 7552.79038) (15546.75713 6591.25215)))
("SF_ARCHITECTURE" 0 ((15546.75713 7567.87330) (15558.07127 7571.64400)))
("SF_PLANTING" 0 ((15561.83824 3668.92952) (15557.01346 3695.32387) (15546.75905 3706.63609)))
("SF_PLANTING" 0 ((15558.07127 3642.53394) (15546.75905 3653.84615)))
("SF_PLANTING" 0 ((15550.52602 4204.37364) (15564.56143 4162.89593) (15570.43846 4128.95928) (15581.89152 4098.94774)
(15588.23529 4095.02262)))
("SF_PLANTING" 0 ((15569.38348 3944.19265) (15560.78326 3963.04649) (15550.52602 3974.35939)))
("SF_PLANTING" 0 ((15554.29864 4000.75373) (15550.52602 3974.35939)))
("SF_PLANTING" 0 ((15558.06934 1155.73247) (15550.52602 1127.45192)))
("SF_PLANTING" 0 ((15588.23529 1052.03620) (15569.38348 1065.91482) (15550.52602 1070.89084)))
("SF_PLANTING" 0 ((15550.52602 1070.89084) (15558.07127 1089.74265)))
("SF_PLANTING" 0 ((15550.52602 354.44853) (15554.45192 320.51188) (15561.83824 309.19966)))
("SF_PLANTING" 0 ((15554.29864 373.30317) (15550.52602 354.44853)))
("SF_SOLAR" 0 ((15554.29864 8024.13281) (15558.07127 8031.67421)))
("SF_PLANTING" 0 ((15554.29864 4000.75373) (15561.83824 4000.75373)))
("SF_PLANTING" 0 ((15584.46267 373.30317) (15554.29864 373.30317)))
("SF_PLANTING" 0 ((15554.29864 373.30317) (15554.44638 395.92760) (15559.26018 411.00962) (15568.32568 426.09446)
(15579.79943 463.80090) (15595.77489 486.42534)))
("SF_MASONRY_AND_ARCH" 0 ((15558.06934 1155.73247) (15573.15045 1158.81459) (15583.40769 1168.92817) (15588.08756
1180.24038) (15592.00600 1221.71946) (15592.00600 2175.71618) (15592.00600 2185.82432) (15603.32014 2187.01527)
(15618.40124 2183.10328) (15618.40124 2171.94570) (15618.40124 1168.92817)))
("SF_SOLAR" 0 ((15558.07127 7978.88394) (15558.07127 7990.19615)))
("SF_SOLAR" 0 ((15558.07127 7948.71799) (15558.07127 7960.03020)))
("SF_SOLAR" 0 ((15558.07127 7929.86425) (15558.07127 7914.78133)))
("SF_SOLAR" 0 ((15561.83824 7892.15690) (15558.07127 7884.61538)))
("SF_PLANTING" 0 ((15558.07127 4257.16482) (15561.99434 4245.85882) (15576.92308 4238.31029)))
("SF_PLANTING" 0 ((15573.15045 4272.24695) (15558.07127 4257.16482)))
("SF_PLANTING" 0 ((15558.07127 3642.53394) (15558.07127 3634.99287)))
("SF_PLANTING" 0 ((15558.07127 3642.53394) (15561.83824 3668.92952)))
("SF_PLANTING" 0 ((15588.23529 3627.45057) (15558.07127 3634.99287)))
("SF_SOLAR" 0 ((15757.91855 8141.02557) (15576.92308 8141.03224) (15561.83824 8148.56719)))
("SF_SOLAR" 0 ((15780.54299 8159.87941) (15769.23077 8163.64344) (15573.15882 8163.49536) (15566.66719 8159.72466)
(15561.83824 8148.56719)))
("SF_PLANTING" 0 ((15612.74321 4000.75373) (15561.83824 4000.75373)))
("SF_PLANTING" 0 ((15614.63235 3823.52941) (15576.92308 3827.44842) (15561.83824 3834.84163)))
("SF_PLANTING" 0 ((15561.83824 3834.84163) (15565.61086 3861.23722)))
("SF_PLANTING" 0 ((15576.92308 3774.50939) (15584.47104 3773.30554) (15599.17885 3760.26244) (15600.75170 3744.34389)
(15614.32986 3725.49061) (15595.62851 3695.32455) (15561.83824 3668.92952)))
("SF_PLANTING" 0 ((15561.83824 309.19966) (15599.54751 323.23360) (15614.63235 324.28450)))
("SF_PLANTING" 0 ((15561.83824 237.55656) (15580.69570 233.78676) (15622.17195 237.55656)))
("SF_PLANTING" 0 ((15561.83824 237.55656) (15565.61086 256.41120)))
("SF_SOLAR" 0 ((15565.61086 7861.99095) (15569.38348 7873.30317)))
("SF_PLANTING" 0 ((15565.61086 3861.23722) (15565.61086 3876.31934)))
("SF_PLANTING" 0 ((15599.54751 3917.79830) (15591.85735 3898.94446) (15565.61086 3876.31934)))
("SF_PLANTING" 0 ((15610.85973 3861.23722) (15565.61086 3861.23722)))
("SF_PLANTING" 0 ((15565.61086 972.85068) (15573.30656 947.65984) (15592.00792 945.25781) (15603.32014 938.91403)))
("SF_PLANTING" 0 ((15565.61086 972.85068) (15569.38348 1010.55713)))
("SF_SOLAR" 0 ((15569.38348 8171.19163) (15573.15045 8197.58665)))
("SF_PLANTING" 0 ((15569.38348 3944.19265) (15588.08756 3935.59491) (15599.54751 3917.79830)))
("SF_PLANTING" 0 ((15569.38348 3378.58247) (15580.69570 3378.58247)))
("SF_PLANTING" 0 ((15592.00792 1033.18156) (15569.38348 1010.55713)))
("SF_SOLAR" 0 ((15592.00792 7843.13722) (15573.15045 7843.13722)))
("SF_PLANTING" 0 ((15573.15045 4272.24695) (15576.77534 4264.69966) (15576.92308 4238.31029)))
("SF_ARCHITECTURE" 0 ((15573.15045 4272.24695) (15569.38156 4622.92568) (15576.92308 4645.55011) (15573.15238
5512.82093) (15576.92308 5531.67421)))
("SF_SOLAR" 0 ((15576.92308 8122.17195) (15580.69570 8133.48416)))
("SF_ARCHITECTURE" 0 ((15576.92308 5531.67421) (15614.62398 5531.52613) (15622.17195 5527.90305)))
("SF_PLANTING" 0 ((15610.85973 4215.68586) (15580.84898 4228.05475) (15576.92308 4238.31029)))
("SF_PLANTING" 0 ((15576.92308 3344.64581) (15583.41595 3344.94819) (15588.08756 3355.95803) (15587.03948 3374.65656)
(15580.69570 3378.58247)))
("SF_SOLAR" 0 ((15580.69570 8069.38167) (15580.69570 8084.46448)))
("SF_SOLAR" 0 ((15580.69570 8031.67421) (15580.69570 8024.13281)))
("SF_SOLAR" 0 ((15580.69570 7948.71799) (15584.46267 7960.03020)))
("SF_SOLAR" 0 ((15580.69570 7926.09355) (15580.69570 7914.78133)))
("SF_PLANTING" 0 ((15580.69570 3412.51912) (15580.69570 3378.58247)))
("SF_MASONRY_AND_ARCH" 0 ((15584.46267 2960.03043) (15584.46267 3235.29412)))
("SF_PLANTING" 0 ((15614.63235 3235.29412) (15599.54751 3239.06459) (15584.46267 3235.29412)))
("SF_MASONRY_AND_ARCH" 0 ((15584.46267 2960.03043) (15614.63235 2960.03043)))
("SF_PLANTING" 0 ((15599.54751 369.53337) (15588.23529 369.53337) (15584.46267 373.30317)))
("SF_PLANTING" 0 ((15584.46267 373.30317) (15585.52048 384.61889) (15592.15430 395.55962) (15603.31176 394.72557)
(15614.63235 380.84559)))
("SF_SOLAR" 0 ((15588.23529 7990.19615) (15588.23529 7978.88394)))
("SF_PLANTING" 0 ((15612.74321 4000.75373) (15609.80339 4027.14932) (15593.06290 4064.85713) (15588.23529 4095.02262)))
("SF_PLANTING" 0 ((15603.32014 4121.41821) (15598.35170 4106.33484) (15588.23529 4095.02262)))
("SF_PLANTING" 0 ((15588.23529 3627.45057) (15589.29163 3616.13903) (15605.88439 3582.20860) (15603.32014 3574.66063)))
("SF_PLANTING" 0 ((15588.23529 3627.45057) (15614.63235 3649.91403) (15633.48416 3645.10724) (15644.79638 3634.99287)))
("SF_PLANTING" 0 ((15592.00792 1044.49378) (15588.23529 1052.03620)))
("SF_PLANTING" 0 ((15610.85973 1127.45192) (15595.93100 1119.76109) (15589.28473 1104.82749) (15588.23529 1052.03620)))
("SF_ARCHITECTURE" 0 ((15592.00792 7567.87330) (15603.31821 7564.10260)))
("SF_PLANTING" 0 ((15592.00792 1033.18156) (15592.00792 1044.49378)))
("SF_PLANTING" 0 ((15592.00792 1044.49378) (15618.24604 1067.11821) (15622.17195 1078.43043)))
("SF_PLANTING" 0 ((15592.00792 1033.18156) (15622.17195 1021.88314) (15663.64819 1033.18156)))
("SF_SOLAR" 0 ((15595.77489 7861.99095) (15599.70079 7869.82873) (15625.93620 7869.38439) (15633.48416 7865.76165)))
("SF_PLANTING" 0 ((15641.02376 3929.11052) (15625.94457 3918.85441) (15599.54751 3917.79830)))
("SF_MASONRY_AND_ARCH" 0 ((15599.54751 2631.97613) (15614.63235 2635.74661) (15671.19344 2635.74661) (15682.50566
2635.74661)))
("SF_PLANTING" 0 ((15599.54751 444.94627) (15633.33088 414.77466) (15638.45950 395.92760) (15650.45249 380.84559)))
("SF_PLANTING" 0 ((15599.54751 369.53337) (15604.52285 339.37342) (15614.63235 331.82410)))
("SF_PLANTING" 0 ((15599.54751 369.53337) (15614.63235 380.84559)))
("SF_PLANTING" 0 ((15599.54751 275.26301) (15620.96776 271.33857) (15622.17195 237.55656)))
("SF_PLANTING" 0 ((15603.31821 7564.10260) (15603.31821 6564.85645)))
("SF_ARCHITECTURE" 0 ((15607.08710 7567.87330) (15603.31821 7564.10260)))
("SF_PLANTING" 0 ((15761.69118 6561.08597) (15693.81787 6561.23428) (15674.96041 6564.85645) (15629.71154 6561.09253)
(15603.31821 6564.85645)))
("SF_SOLAR" 0 ((15603.32014 8080.69389) (15603.32014 8069.38167)))
("SF_SOLAR" 0 ((15603.32014 8020.36199) (15603.32014 8031.67421)))
("SF_PLANTING" 0 ((15603.32014 938.91403) (15603.32014 912.51980)))
("SF_PLANTING" 0 ((15610.85973 946.45645) (15607.08710 946.45645) (15603.32014 938.91403)))
("SF_PLANTING" 0 ((15652.33597 901.20758) (15622.17195 901.35532) (15603.32014 912.51980)))
("SF_SOLAR" 0 ((15610.85973 7948.71799) (15622.17195 7960.03020)))
("SF_SOLAR" 0 ((15610.85973 7892.15690) (15610.85973 7884.61538)))
("SF_PLANTING" 0 ((15625.94457 4177.97930) (15615.82817 4189.29152) (15610.85973 4215.68586)))
("SF_ARCHITECTURE" 0 ((15610.85973 4215.68586) (15622.16505 4306.18360) (15625.94864 4638.00905) (15629.70747
4656.86233) (15629.71991 4883.10667) (15633.47726 4901.96120) (15629.71991 4932.12670) (15629.70747 5199.84876)
(15625.94864 5218.70328) (15629.71154 5471.34197)))
("SF_PLANTING" 0 ((15614.63235 3823.52941) (15614.48314 3853.68869) (15610.85973 3861.23722)))
("SF_PLANTING" 0 ((15610.85973 3861.23722) (15614.78563 3867.58066) (15633.48416 3869.83495) (15652.33597 3880.09050)))
("SF_PLANTING" 0 ((15610.85973 1127.45192) (15619.91833 1116.13971) (15618.54853 1089.74265) (15622.17195 1078.43043)))
("SF_PLANTING" 0 ((15610.85973 1127.45192) (15618.40124 1168.92817)))
("SF_PLANTING" 0 ((15610.85973 946.45645) (15633.48416 946.30803) (15652.33597 938.91403)))
("SF_PLANTING" 0 ((15610.85973 946.45645) (15629.71991 984.01448) (15644.79638 991.55000) (15663.64819 987.93269)))
("SF_PLANTING" 0 ((15612.74321 4000.75373) (15629.71154 3981.90045)))
("SF_PLANTING" 0 ((15612.74321 4000.75373) (15641.02376 4015.83710)))
("SF_PLANTING" 0 ((15614.63235 3823.52941) (15641.02376 3819.75826)))
("SF_PLANTING" 0 ((15614.63235 3235.29412) (15644.79638 3235.29412)))
("SF_MASONRY_AND_ARCH" 0 ((15614.63235 3235.29412) (15614.63235 2960.03043)))
("SF_MASONRY_AND_ARCH" 0 ((15614.63235 2960.03043) (15648.56900 2960.03043)))
("SF_PLANTING" 0 ((15614.63235 380.84559) (15650.45249 380.84559)))
("SF_PLANTING" 0 ((15614.63235 331.82410) (15614.63235 324.28450)))
("SF_PLANTING" 0 ((15614.63235 331.82410) (15652.33597 358.22115)))
("SF_PLANTING" 0 ((15656.10860 301.66007) (15629.86210 302.86346) (15614.63235 324.28450)))
("SF_PLANTING" 0 ((15663.64819 1168.92817) (15618.40124 1168.92817)))
("SF_SOLAR" 0 ((15637.25679 8092.00611) (15633.48416 8088.23529) (15622.17195 8088.23529)))
("SF_ARCHITECTURE" 0 ((15633.48416 5527.90305) (15622.17195 5527.90305)))
("SF_ARCHITECTURE" 0 ((15629.71154 5471.34197) (15614.63043 5478.89050) (15614.63043 5486.42534) (15614.63043
5509.04977) (15622.17195 5527.90305)))
("SF_PLANTING" 0 ((15669.30430 1082.20305) (15622.17195 1078.43043)))
("SF_PLANTING" 0 ((15674.96041 245.09898) (15663.64819 237.71120) (15622.17195 237.55656)))
("SF_SOLAR" 0 ((15625.94457 8069.38167) (15625.94457 8080.69389)))
("SF_SOLAR" 0 ((15625.94457 8031.67421) (15625.94457 8020.36199)))
("SF_SOLAR" 0 ((15625.94457 7978.88394) (15625.94457 7990.19615)))
("SF_SOLAR" 0 ((15629.71154 7937.40577) (15625.94457 7914.78133)))
("SF_ARCHITECTURE" 0 ((15625.94457 7571.64400) (16263.19570 7571.63744) (16278.28054 7567.87330)))
("SF_PLANTING" 0 ((15625.94457 4177.97930) (15626.09095 4140.27149) (15630.76244 4129.11391) (15637.25679 4125.18812)))
("SF_PLANTING" 0 ((15625.94457 4177.97930) (15647.36346 4196.83258) (15660.93620 4245.85260) (15686.27262 4279.78925)))
("SF_SOLAR" 0 ((15629.71154 8118.40113) (15629.71154 8133.48416)))
("SF_SOLAR" 0 ((15701.35747 8039.21561) (15681.31256 7997.73756) (15647.51810 7948.72455) (15629.71154 7937.40577)))
("SF_ARCHITECTURE" 0 ((15629.71154 5471.34197) (15640.87738 5493.96640) (15640.87048 5516.59084) (15633.48416
5527.90305)))
("SF_PLANTING" 0 ((15641.02376 3929.11052) (15633.63190 3944.19265) (15629.71154 3981.90045)))
("SF_PLANTING" 0 ((15629.71154 3981.90045) (15643.59219 3996.98382) (15641.02376 4015.83710)))
("SF_SOLAR" 0 ((15641.02376 7858.22025) (15633.48416 7854.44943)))
("SF_ARCHITECTURE" 0 ((15693.81787 5527.90305) (15671.19344 5535.44536) (15644.79638 5535.29038) (15633.48416
5527.90305)))
("SF_PLANTING" 0 ((15641.02376 4015.83710) (15644.78948 4049.77376) (15637.25679 4125.18812)))
("SF_PLANTING" 0 ((15644.79638 4140.27149) (15644.79638 4132.73043) (15637.25679 4125.18812)))
("SF_PLANTING" 0 ((15671.19344 3710.40724) (15653.39378 3725.49061) (15638.45950 3748.11437) (15637.25679 3759.42726)))
("SF_SOLAR" 0 ((15641.02376 7858.22025) (15644.79638 7850.67873)))
("SF_SOLAR" 0 ((15641.02376 7858.22025) (15659.88122 7895.92760)))
("SF_PLANTING" 0 ((15656.10860 3925.33937) (15641.02376 3929.11052)))
("SF_PLANTING" 0 ((15720.20928 3812.21719) (15701.35747 3797.28880) (15656.10860 3797.28880) (15642.22930 3808.44604)
(15641.02376 3819.75826)))
("SF_PLANTING" 0 ((15656.10860 3842.38269) (15641.02376 3819.75826)))
("SF_PLANTING" 0 ((15644.79638 6836.34966) (15659.88122 6836.34966)))
("SF_PLANTING" 0 ((15678.73303 3627.45057) (15671.18507 3620.06414) (15652.34434 3620.06414) (15646.00057 3623.83462)
(15644.79638 3634.99287)))
("SF_PLANTING" 0 ((15671.19344 3642.53394) (15644.79638 3634.99287)))
("SF_MASONRY_AND_ARCH" 0 ((15644.79638 3235.29412) (15644.94412 3174.96256) (15648.56063 3159.87907) (15648.56900
2960.03043)))
("SF_PLANTING" 0 ((15644.79638 3235.29412) (15659.88122 3239.06459) (15693.81787 3235.29412)))
("SF_SOLAR" 0 ((16315.98982 7835.59581) (15712.66968 7835.59581) (15697.58484 7835.59581) (15648.56900 7839.36652)))
("SF_MASONRY_AND_ARCH" 0 ((15693.81787 2963.80090) (15674.96041 2956.40769) (15648.56900 2960.03043)))
("SF_PLANTING" 0 ((15650.45249 380.84559) (15652.33597 358.22115)))
("SF_PLANTING" 0 ((15686.27262 418.55204) (15650.45249 380.84559)))
("SF_PLANTING" 0 ((15656.10860 3842.38269) (15655.96086 3872.54253) (15652.33597 3880.09050)))
("SF_PLANTING" 0 ((15656.10860 3898.94378) (15652.48518 3895.01889) (15652.33597 3880.09050)))
("SF_PLANTING" 0 ((15667.42081 1127.45192) (15656.10860 1127.45192) (15652.33597 1123.67930)))
("SF_PLANTING" 0 ((15652.33597 901.20758) (15652.33597 938.91403)))
("SF_PLANTING" 0 ((15667.42081 969.08088) (15652.33597 938.91403)))
("SF_PLANTING" 0 ((15652.33597 901.20758) (15667.42081 897.59027) (15697.58484 904.97738)))
("SF_PLANTING" 0 ((15671.19344 350.67873) (15652.33597 358.22115)))
("SF_PLANTING" 0 ((15656.10860 3925.33937) (15656.10860 3898.94378)))
("SF_PLANTING" 0 ((15686.27262 3944.19265) (15667.42081 3935.59559) (15656.10860 3925.33937)))
("SF_PLANTING" 0 ((15705.13009 3895.17387) (15663.65656 3895.32172) (15656.10860 3898.94378)))
("SF_PLANTING" 0 ((15656.10860 3842.38269) (15674.96041 3834.98971) (15712.66968 3831.07048)))
("SF_PLANTING" 0 ((15656.10860 301.66007) (15657.31278 279.03563) (15669.98790 263.95079) (15674.96041 245.09898)))
("SF_PLANTING" 0 ((15656.10860 301.66007) (15663.65656 308.00249) (15674.96041 309.19966)))
("SF_SOLAR" 0 ((15659.88122 8088.23529) (15659.88122 8073.15226)))
("SF_SOLAR" 0 ((15659.88122 7944.94717) (15667.42081 7937.40577)))
("SF_PLANTING" 0 ((15659.88122 6836.34966) (15672.24842 6787.48518) (15712.66968 6779.78857)))
("SF_PLANTING" 0 ((15659.88122 6836.34966) (15663.80430 6842.70023) (15682.50566 6847.65532) (15769.23077 6847.51403)
(15788.08258 6840.12093)))
("SF_PLANTING" 0 ((15663.64819 1168.92817) (15667.27308 1161.38100) (15667.42081 1138.76414)))
("SF_PLANTING" 0 ((15674.96041 1006.78733) (15669.99480 1025.63439) (15663.64819 1033.18156)))
("SF_PLANTING" 0 ((15671.19344 1052.03620) (15663.64819 1033.18156)))
("SF_PLANTING" 0 ((15667.42081 969.08088) (15663.64819 987.93269)))
("SF_PLANTING" 0 ((15663.64819 987.93269) (15674.96041 1006.78733)))
("SF_SOLAR" 0 ((15667.42081 8024.13281) (15667.42081 8031.67421)))
("SF_PLANTING" 0 ((15667.42081 1127.45192) (15667.42081 1138.76414)))
("SF_PLANTING" 0 ((15723.98190 1157.61595) (15716.43394 1161.24016) (15701.36437 1160.18371) (15686.26855 1143.73190)
(15667.42081 1138.76414)))
("SF_PLANTING" 0 ((15667.42081 1127.45192) (15669.30430 1082.20305)))
("SF_PLANTING" 0 ((15667.42081 969.08088) (15686.12624 964.10486) (15692.76007 953.99604) (15697.58484 904.97738)))
("SF_PLANTING" 0 ((15671.19344 1052.03620) (15669.30430 1082.20305)))
("SF_PLANTING" 0 ((15742.83371 1134.99152) (15723.98190 1123.53224) (15686.12624 1083.40645) (15669.30430 1082.20305)))
("SF_SOLAR" 0 ((15671.19344 8133.48416) (15671.19344 8118.40113)))
("SF_PLANTING" 0 ((15671.19344 3710.40724) (15671.19344 3702.86618)))
("SF_PLANTING" 0 ((15671.19344 3710.40724) (15690.04525 3721.71946)))
("SF_PLANTING" 0 ((15678.73303 3627.45057) (15671.19344 3642.53394)))
("SF_PLANTING" 0 ((15705.13009 3661.38722) (15697.58077 3667.73133) (15686.28100 3667.72477) (15671.19344 3642.53394)))
("SF_PLANTING" 0 ((15671.19344 1052.03620) (15708.89706 1060.77579) (15776.77036 1127.29661) (15788.08258 1131.22172)))
("SF_PLANTING" 0 ((15708.89706 350.67873) (15671.19344 350.67873)))
("SF_PLANTING" 0 ((15671.19344 350.67873) (15674.96041 309.19966)))
("SF_PLANTING" 0 ((15727.75452 991.70532) (15674.96041 1006.78733)))
("SF_PLANTING" 0 ((15705.13009 290.34785) (15690.04525 295.17398) (15674.96041 309.19966)))
("SF_PLANTING" 0 ((15705.13009 245.09898) (15674.96041 245.09898)))
("SF_PLANTING" 0 ((15678.73303 3627.45057) (15690.04525 3630.02410) (15712.51640 3626.24672) (15723.82862 3597.28507)
(15720.05600 3586.12749) (15701.35747 3578.58575) (15693.82195 3579.63529) (15686.27262 3589.74333)))
("SF_SOLAR" 0 ((15686.27262 7986.42534) (15686.27262 7975.11312)))
("SF_PLANTING" 0 ((15701.35747 4268.47704) (15686.27262 4279.78925)))
("SF_ARCHITECTURE" 0 ((15686.27262 4279.78925) (15690.03835 4298.64253) (15690.05215 4600.30124) (15693.80950
4619.15577) (15693.80950 5361.99095) (15690.04525 5399.69876) (15693.80950 5422.32319) (15693.81787 5527.90305)))
("SF_PLANTING" 0 ((15686.27262 3944.19265) (15720.20928 3944.19265)))
("SF_PLANTING" 0 ((15686.27262 3944.19265) (15686.42183 3974.35939) (15693.81787 4008.29604)))
("SF_PLANTING" 0 ((15686.27262 467.57070) (15682.50566 452.48869) (15686.27262 418.55204)))
("SF_PLANTING" 0 ((15686.27262 418.55204) (15720.20928 426.09446)))
("SF_SOLAR" 0 ((15727.75452 7873.30317) (15690.04525 7873.30317)))
("SF_PLANTING" 0 ((15690.04525 4113.87590) (15693.66867 4106.32862) (15693.66867 4068.62704) (15686.28100 4019.60826)
(15687.47127 4012.22093) (15693.81787 4008.29604)))
("SF_PLANTING" 0 ((15690.04525 4113.87590) (15683.70147 4117.80170) (15682.65204 4132.73043) (15687.33043 4143.89423)
(15697.58484 4151.58371)))
("SF_PLANTING" 0 ((15690.04525 4113.87590) (15701.20419 4128.95928) (15697.58484 4151.58371)))
("SF_PLANTING" 0 ((15690.04525 3721.71946) (15691.24106 3736.79593) (15697.58484 3744.34389)))
("SF_PLANTING" 0 ((15690.04525 3721.71946) (15708.89706 3721.87410) (15720.20928 3729.26052)))
("SF_SOLAR" 0 ((15693.81787 8118.40113) (15693.81787 8125.94276)))
("SF_SOLAR" 0 ((15693.81787 8088.23529) (15693.81787 8069.38167)))
("SF_ARCHITECTURE" 0 ((15765.45814 5527.90305) (15739.06674 5535.44536) (15708.89706 5535.29038) (15693.81787
5527.90305)))
("SF_PLANTING" 0 ((15735.29412 4057.31482) (15717.49729 4038.46154) (15708.74378 4019.60826) (15693.81787 4008.29604)))
("SF_MASONRY_AND_ARCH" 0 ((15693.81787 2963.80090) (15693.81787 3235.29412)))
("SF_PLANTING" 0 ((15742.83371 3235.29412) (15727.75452 3239.06459) (15693.81787 3235.29412)))
("SF_MASONRY_AND_ARCH" 0 ((15750.37896 2967.57138) (15731.52149 2956.41380) (15708.89706 2956.40769) (15693.81787
2963.80090)))
("SF_SOLAR" 0 ((15701.35747 7990.19615) (15697.58484 8005.27896)))
("SF_SOLAR" 0 ((15697.58484 7884.61538) (15697.58484 7892.15690)))
("SF_PLANTING" 0 ((15716.44231 4234.54038) (15705.27647 4204.37364) (15697.58484 4151.58371)))
("SF_MASONRY_AND_ARCH" 0 ((15716.44231 2394.41957) (15697.58484 2398.19005)))
("SF_PLANTING" 0 ((15735.29412 904.97738) (15697.58484 904.97738)))
("SF_SOLAR" 0 ((15701.35747 8039.21561) (15727.75452 8065.61086)))
("SF_PLANTING" 0 ((15731.52149 460.03111) (15723.82862 475.11312) (15691.24943 505.27998) (15691.24943 520.21357)
(15701.35747 527.90441)))
("SF_ARCHITECTURE" 0 ((15837.10407 5599.54751) (15705.13009 5599.54751)))
("SF_PLANTING" 0 ((15705.13009 3895.17387) (15716.44231 3872.54943)))
("SF_PLANTING" 0 ((15750.37896 3906.48609) (15720.20928 3906.33111) (15705.13009 3895.17387)))
("SF_PLANTING" 0 ((15708.89706 286.57523) (15708.89706 290.34785) (15705.13009 290.34785)))
("SF_PLANTING" 0 ((15708.89706 286.57523) (15705.13009 290.34785)))
("SF_PLANTING" 0 ((15708.89706 350.67873) (15705.13009 290.34785)))
("SF_PLANTING" 0 ((15742.83371 245.09898) (15705.13009 245.09898)))
("SF_PLANTING" 0 ((15708.89706 286.57523) (15705.13009 245.09898)))
("SF_PLANTING" 0 ((15735.29412 6885.36980) (15723.98190 6884.16550) (15708.89706 6874.05758)))
("SF_PLANTING" 0 ((15744.72285 361.99095) (15708.89706 350.67873)))
("SF_PLANTING" 0 ((15708.89706 286.57523) (15731.52149 286.57523)))
("SF_PLANTING" 0 ((15761.69118 6561.08597) (15765.45407 6576.16867) (15765.31176 6696.83258) (15756.72274 6726.85045)
(15727.75452 6739.36697) (15717.64502 6749.62319) (15712.66968 6779.78857)))
("SF_PLANTING" 0 ((15776.77036 6783.55984) (15723.98190 6783.41154) (15712.66968 6779.78857)))
("SF_PLANTING" 0 ((15720.20928 3812.21719) (15712.66968 3831.07048)))
("SF_PLANTING" 0 ((15716.44231 3872.54943) (15712.66968 3831.07048)))
("SF_SOLAR" 0 ((15716.44231 8133.48416) (15716.44231 8118.40113)))
("SF_SOLAR" 0 ((15723.98190 8027.90339) (15716.44231 8039.21561)))
("SF_PLANTING" 0 ((15716.44231 3872.54943) (15750.37896 3872.54943)))
("SF_PLANTING" 0 ((15716.44231 3736.80283) (15720.20928 3729.26052)))
("SF_MASONRY_AND_ARCH" 0 ((15716.44231 2349.17070) (15716.44231 2394.41957)))
("SF_MASONRY_AND_ARCH" 0 ((15931.37443 2398.19005) (15920.06222 2394.42579) (15716.44231 2394.41957)))
("SF_MASONRY_AND_ARCH" 0 ((15731.52149 2266.21391) (15723.98190 2269.98518) (15716.44231 2266.21391)))
("SF_PLANTING" 0 ((15727.75452 976.62048) (15723.98190 976.62048) (15716.44231 965.30826)))
("SF_SOLAR" 0 ((15723.98190 7963.80090) (15720.20928 7971.34231)))
("SF_PLANTING" 0 ((15720.20928 3944.19265) (15725.03824 3970.58824) (15732.57930 3985.67161) (15754.14593 4004.52489)))
("SF_PLANTING" 0 ((15720.20928 3944.19265) (15739.05837 3949.16143) (15750.52534 3961.84932) (15769.23077 3970.58824)))
("SF_PLANTING" 0 ((15720.20928 3812.21719) (15739.06674 3812.21719)))
("SF_PLANTING" 0 ((15901.20475 3721.71946) (15878.58032 3729.11267) (15788.08258 3729.26742) (15765.45814 3733.03167)
(15720.20928 3729.26052)))
("SF_MASONRY_AND_ARCH" 0 ((15720.20928 2665.91278) (15731.52149 2662.14152)))
("SF_MASONRY_AND_ARCH" 0 ((15720.20928 2300.15057) (15720.20928 2315.23405)))
("SF_MASONRY_AND_ARCH" 0 ((15765.45814 2315.23405) (15746.60633 2319.00452) (15720.20928 2315.23405)))
("SF_MASONRY_AND_ARCH" 0 ((15806.94005 2115.38462) (15805.88914 2096.53066) (15795.61946 2078.88156) (15720.20928
2077.67749)))
("SF_PLANTING" 0 ((15799.39480 1251.88631) (15727.75860 1252.03959) (15720.20928 1259.42590)))
("SF_PLANTING" 0 ((15744.72285 361.99095) (15746.45860 384.61538) (15741.78699 399.69740) (15720.20928 426.09446)))
("SF_PLANTING" 0 ((15731.52149 460.03111) (15720.20928 426.09446)))
("SF_MASONRY_AND_ARCH" 0 ((15723.98190 2028.65735) (15739.06674 2032.27398) (15757.91855 2028.67048) (15810.70701
2032.42240) (15848.41629 2024.88688)))
("SF_MASONRY_AND_ARCH" 0 ((15723.98190 1670.43744) (15818.25226 1670.43744)))
("SF_PLANTING" 0 ((15791.85520 1289.59276) (15742.83371 1289.44502) (15723.98190 1282.05034)))
("SF_SOLAR" 0 ((15727.75452 8065.61086) (15735.29412 8058.06946)))
("SF_SOLAR" 0 ((15727.75452 8065.61086) (15739.06674 8099.54751)))
("SF_MASONRY_AND_ARCH" 0 ((15844.64367 1907.99423) (15795.62783 1900.60023) (15727.75452 1900.45249)))
("SF_MASONRY_AND_ARCH" 0 ((15765.45814 1512.06731) (15727.75452 1515.83710)))
("SF_PLANTING" 0 ((15727.75452 1327.29921) (15784.31561 1327.44762) (15818.25226 1334.54548) (15833.33145 1331.22511)
(15852.18891 1334.84163)))
("SF_PLANTING" 0 ((15727.75452 976.62048) (15727.75452 991.70532)))
("SF_PLANTING" 0 ((15727.75452 991.70532) (15750.37896 1010.55713)))
("SF_PLANTING" 0 ((15727.75452 976.62048) (15795.62783 953.99604)))
("SF_PLANTING" 0 ((15735.29412 904.97738) (15727.75452 938.91403)))
("SF_MASONRY_AND_ARCH" 0 ((15731.52149 1459.27602) (15761.69118 1459.27602)))
("SF_PLANTING" 0 ((15731.52149 460.03111) (15750.37896 463.80090)))
("SF_PLANTING" 0 ((15742.83371 260.18100) (15736.48993 267.72828) (15731.52149 286.57523)))
("SF_PLANTING" 0 ((15750.37896 305.42986) (15731.52149 286.57523)))
("SF_PLANTING" 0 ((15765.45814 4317.49581) (15750.37704 4307.24027) (15735.29412 4306.18360)))
("SF_PLANTING" 0 ((15735.29412 4057.31482) (15757.91855 4038.46154)))
("SF_PLANTING" 0 ((15735.29412 4057.31482) (15765.45814 4144.04265)))
("SF_PLANTING" 0 ((15735.29412 904.97738) (15750.37896 901.35464) (15803.16742 901.05226) (15810.55373 897.28167)
(15814.32636 889.89536) (15813.27545 863.65362) (15799.39480 855.95781) (15784.31561 855.95781)))
("SF_SOLAR" 0 ((15780.54299 8159.87941) (15779.33880 8152.33122) (15739.06674 8099.54751)))
("SF_PLANTING" 0 ((15803.16742 3800.90498) (15784.31561 3793.51176) (15769.23077 3793.51176) (15746.61324 3801.96165)
(15739.06674 3812.21719)))
("SF_PLANTING" 0 ((15757.91855 3831.07048) (15739.06674 3812.21719)))
("SF_MASONRY_AND_ARCH" 0 ((15757.91855 2628.20486) (15746.61324 2635.74661) (15739.06674 2635.74661)))
("SF_PLANTING" 0 ((15750.37896 1010.55713) (15749.17342 1021.86934) (15739.06674 1033.18156)))
("SF_PLANTING" 0 ((15742.83371 3235.29412) (15761.69118 3235.29412)))
("SF_PLANTING" 0 ((15742.83371 3235.29412) (15739.22002 3208.89921) (15742.98982 3201.36437) (15754.14593 3193.81572)))
("SF_PLANTING" 0 ((15742.83371 245.09898) (15742.83371 260.18100)))
("SF_PLANTING" 0 ((15787.33009 289.59253) (15765.45814 268.92059) (15742.83371 260.18100)))
("SF_PLANTING" 0 ((15742.83371 245.09898) (15754.14593 234.98394) (15769.23077 230.16256) (15780.54299 231.07127)
(15799.39480 241.32636)))
("SF_PLANTING" 0 ((15744.72285 361.99095) (15791.85520 361.99095)))
("SF_PLANTING" 0 ((15744.72285 361.99095) (15742.98292 343.13631) (15750.37896 305.42986)))
("SF_PLANTING" 0 ((15750.37896 3906.48609) (15750.37896 3872.54943)))
("SF_PLANTING" 0 ((15750.37896 3906.48609) (15769.23077 3910.25600)))
("SF_PLANTING" 0 ((15780.54299 3865.00713) (15761.69118 3865.16210) (15750.37896 3872.54943)))
("SF_MASONRY_AND_ARCH" 0 ((15803.16742 2960.03043) (15795.61946 2956.40690) (15773.00339 2956.40690) (15750.37896
2967.57138)))
("SF_MASONRY_AND_ARCH" 0 ((15750.37896 2967.57138) (15754.14593 3193.81572)))
("SF_PLANTING" 0 ((15750.37896 1010.55713) (15760.48563 999.25249) (15761.69118 991.70532)))
("SF_PLANTING" 0 ((15791.85520 361.99095) (15787.93620 399.69740) (15779.34717 426.09446) (15750.37896 463.80090)))
("SF_PLANTING" 0 ((15773.00339 497.73756) (15750.37896 463.80090)))
("SF_PLANTING" 0 ((15787.33009 289.59253) (15769.23077 304.22500) (15750.37896 305.42986)))
("SF_PLANTING" 0 ((15754.14593 4004.52489) (15769.23077 3989.44152)))
("SF_PLANTING" 0 ((15754.14593 4004.52489) (15757.77081 4012.07285) (15757.91855 4038.46154)))
("SF_PLANTING" 0 ((15761.69118 3235.29412) (15761.53507 3205.12794) (15754.14593 3193.81572)))
("SF_MASONRY_AND_ARCH" 0 ((15754.14593 2266.21391) (15791.85520 2262.44966) (15806.94005 2266.06618) (15904.97738
2266.22014) (15927.60181 2269.98518) (15972.85068 2266.36855) (15991.70249 2269.97896) (16127.44910 2269.97896)
(16142.53394 2266.21391)))
("SF_PLANTING" 0 ((15765.45814 4038.46154) (15757.91855 4038.46154)))
("SF_PLANTING" 0 ((15799.39480 6481.90045) (15776.77036 6482.05509) (15766.66369 6489.44842) (15765.31176 6553.53767)
(15761.69118 6561.08597)))
("SF_PLANTING" 0 ((15806.94005 3235.29412) (15791.85520 3239.06459) (15769.23767 3238.91686) (15761.69118 3235.29412)))
("SF_ARCHITECTURE" 0 ((15765.45814 4317.49581) (15765.45814 5527.90305)))
("SF_ARCHITECTURE" 0 ((15833.33145 5531.67421) (15825.78495 5535.29695) (15780.54299 5535.29038) (15765.45814
5527.90305)))
("SF_PLANTING" 0 ((15765.45814 4317.49581) (15769.23077 4302.41369) (15765.45814 4144.04265)))
("SF_PLANTING" 0 ((15833.33145 4177.97930) (15806.94005 4150.68857) (15788.08258 4144.19050) (15765.45814 4144.04265)))
("SF_PLANTING" 0 ((15765.45814 4038.46154) (15766.65814 4049.77376) (15777.82817 4068.62704) (15795.62783 4083.71041)))
("SF_PLANTING" 0 ((15765.45814 4038.46154) (15788.08258 4039.66606) (15805.72624 4057.31482) (15801.97715 4076.16244)
(15795.62783 4083.71041)))
("SF_MASONRY_AND_ARCH" 0 ((16150.07353 2647.05882) (16089.74548 2633.17398) (16067.12104 2635.74661) (16044.49661
2635.74661) (16025.63914 2635.74661) (15995.47511 2635.74661) (15784.31561 2635.74661) (15765.45814 2635.74661)))
("SF_PLANTING" 0 ((15769.23077 3970.58824) (15769.23077 3989.44152)))
("SF_PLANTING" 0 ((15833.33145 4012.06595) (15799.39480 4011.00984) (15769.23077 3989.44152)))
("SF_PLANTING" 0 ((15769.23077 3970.58824) (15788.08258 3970.58824)))
("SF_PLANTING" 0 ((15784.31561 3898.94378) (15769.23077 3910.25600)))
("SF_PLANTING" 0 ((15882.35294 3955.50486) (15829.56448 3933.93088) (15784.31561 3931.67658) (15769.23077 3910.25600)))
("SF_PLANTING" 0 ((15855.95588 6779.78857) (15844.64367 6783.41154) (15776.77036 6783.55984)))
("SF_PLANTING" 0 ((15776.77036 6783.55984) (15776.91957 6809.95475) (15788.08258 6840.12093)))
("SF_PLANTING" 0 ((15776.77036 595.77771) (15784.30724 610.85973) (15784.31561 855.95781)))
("SF_SOLAR" 0 ((15799.39480 8182.50385) (15795.47172 8171.19163) (15780.54299 8159.87941)))
("SF_PLANTING" 0 ((15780.54299 3865.00713) (15791.84830 3857.45984) (15803.16742 3842.38269)))
("SF_PLANTING" 0 ((15784.31561 3898.94378) (15780.54299 3865.00713)))
("SF_MASONRY_AND_ARCH" 0 ((15780.54299 1459.27602) (15803.16742 1459.27602)))
("SF_SOLAR" 0 ((15788.08258 8133.48416) (15784.31561 8141.02557)))
("SF_PLANTING" 0 ((15784.31561 6907.99423) (15810.70701 6911.76471)))
("SF_PLANTING" 0 ((15784.31561 6742.08145) (15791.86210 6738.45882) (15825.79186 6738.45882) (15852.18891 6745.85192)))
("SF_PLANTING" 0 ((15784.31561 3898.94378) (15825.79186 3899.09219) (15867.26810 3910.10814) (15908.75000 3914.02715)))
("SF_PLANTING" 0 ((15787.33009 289.59253) (15799.24152 271.49321) (15799.39480 241.32636)))
("SF_PLANTING" 0 ((15787.33009 289.59253) (15799.24842 312.97229) (15799.39480 361.99095)))
("SF_PLANTING" 0 ((15787.33009 289.59253) (15814.47964 294.11765)))
("SF_PLANTING" 0 ((15822.01923 6847.66188) (15788.08258 6840.12093)))
("SF_MASONRY_AND_ARCH" 0 ((15806.94005 1512.06731) (15803.16742 1515.83710) (15791.85520 1515.83710)))
("SF_PLANTING" 0 ((15791.85520 361.99095) (15799.39480 361.99095)))
("SF_PLANTING" 0 ((15837.10407 6923.07692) (15825.79186 6924.28122) (15803.17432 6944.49706) (15795.62783 6945.70136)))
("SF_PLANTING" 0 ((15806.94005 4110.10600) (15795.62783 4083.71041)))
("SF_SOLAR" 0 ((15803.16742 8148.56719) (15799.39480 8159.87941)))
("SF_ARCHITECTURE" 0 ((15799.39480 6481.90045) (15800.45260 6025.64095) (15818.25226 6004.21437) (15840.87670
5998.04842) (15886.12557 5974.04174) (15961.53846 5945.25781) (15976.62330 5923.83100)))
("SF_PLANTING" 0 ((15999.24774 6485.67127) (15822.01923 6485.66471) (15799.39480 6481.90045)))
("SF_MASONRY_AND_ARCH" 0 ((15799.39480 2239.81900) (15806.79084 2213.42410) (15810.02771 2168.54389) (15927.60181
2171.93948) (15938.91403 2168.17523)))
("SF_PLANTING" 0 ((15871.04072 493.96776) (15864.69005 490.04186) (15826.84129 403.47002) (15824.58767 380.84559)
(15810.70701 366.81787) (15799.39480 361.99095)))
("SF_PLANTING" 0 ((15799.39480 241.32636) (15822.01923 233.78676) (15897.43778 233.93450) (15912.51697 241.32636)))
("SF_PLANTING" 0 ((15848.41629 3831.07048) (15833.33145 3842.22873) (15803.16742 3842.38269)))
("SF_PLANTING" 0 ((15803.16742 3800.90498) (15803.16742 3842.38269)))
("SF_PLANTING" 0 ((15852.18891 3808.44604) (15837.10407 3801.05962) (15803.16742 3800.90498)))
("SF_MASONRY_AND_ARCH" 0 ((15803.16742 2960.03043) (15829.56448 2960.03043)))
("SF_MASONRY_AND_ARCH" 0 ((15803.16742 2960.03043) (15807.09333 3125.94242) (15810.86312 3133.47726) (15822.01923
3141.02590)))
("SF_MASONRY_AND_ARCH" 0 ((15806.94005 1421.56957) (15806.79084 1451.72873) (15803.16742 1459.27602)))
("SF_MASONRY_AND_ARCH" 0 ((15810.70701 1474.35803) (15803.16742 1459.27602)))
("SF_PLANTING" 0 ((15806.94005 3235.29412) (15829.56448 3235.29412)))
("SF_PLANTING" 0 ((15818.25226 3167.42081) (15803.32070 3186.27477) (15803.31516 3223.98190) (15806.94005 3235.29412)))
("SF_MASONRY_AND_ARCH" 0 ((15810.70701 2477.37557) (15806.94005 2443.43891)))
("SF_MASONRY_AND_ARCH" 0 ((15810.70701 1474.35803) (15806.94005 1512.06731)))
("SF_MASONRY_AND_ARCH" 0 ((16210.40724 1542.23133) (16168.93100 1538.46776) (16146.30656 1541.93586) (16131.22172
1538.46776) (16059.57579 1541.03416) (16040.87172 1537.25667) (16031.98439 1519.76222) (16025.63507 1515.99174)
(15969.07805 1512.36278) (15901.20475 1519.60068) (15806.94005 1512.06731)))
("SF_PLANTING" 0 ((15810.70701 7051.28179) (15837.10407 7046.45532) (15874.81335 7024.88688)))
("SF_MASONRY_AND_ARCH" 0 ((15810.70701 2590.49774) (15818.25226 2605.58043)))
("SF_MASONRY_AND_ARCH" 0 ((15810.70701 1474.35803) (15822.01923 1474.35803) (15825.79186 1478.13066)))
("SF_MASONRY_AND_ARCH" 0 ((15814.47964 1806.18495) (15829.56448 1817.34186) (15938.91403 1817.50204) (15961.53846
1821.26697) (16029.41176 1817.65045) (16039.51980 1825.04434) (16045.69932 1858.81946) (16067.12104 1866.51584)))
("SF_MASONRY_AND_ARCH" 0 ((15814.47964 1745.85124) (15818.25226 1768.47568)))
("SF_PLANTING" 0 ((15814.47964 294.11765) (15844.64367 271.49321)))
("SF_PLANTING" 0 ((15814.47964 294.11765) (15871.04072 335.59672)))
("SF_MASONRY_AND_ARCH" 0 ((15818.25226 3167.42081) (15822.01923 3141.02590)))
("SF_MASONRY_AND_ARCH" 0 ((15818.25226 3167.42081) (15833.17817 3186.27477) (15829.56448 3235.29412)))
("SF_MASONRY_AND_ARCH" 0 ((15818.25226 1719.45701) (15818.25226 1670.43744)))
("SF_MASONRY_AND_ARCH" 0 ((16029.41176 1670.43744) (16014.32692 1670.43744) (15818.25226 1670.43744)))
("SF_PLANTING" 0 ((15818.25226 1248.11369) (15815.54152 1266.96833) (15822.16290 1277.07568) (15829.56448 1278.28054)))
("SF_PLANTING" 0 ((15822.01923 6847.66188) (15837.10407 6837.40645) (15848.41629 6836.35000) (15878.58032 6845.55645)
(15916.28959 6843.89796) (15935.14140 6847.66188)))
("SF_PLANTING" 0 ((15822.01923 6847.66188) (15825.94514 6870.27975) (15878.58032 6900.60079) (15892.46097 6915.52862)
(15893.66516 6923.07692)))
("SF_MASONRY_AND_ARCH" 0 ((15822.01923 3141.02590) (15833.17817 3125.94242) (15829.56448 3016.59152) (15833.32738
2975.11312) (15829.56448 2960.03043)))
("SF_PLANTING" 0 ((15878.58032 3235.29412) (15863.50113 3239.06459) (15837.11097 3238.91686) (15829.56448 3235.29412)))
("SF_MASONRY_AND_ARCH" 0 ((15829.56448 2960.03043) (15867.26810 2956.41380) (15878.58032 2963.80090)))
("SF_PLANTING" 0 ((15829.56448 1289.59276) (15829.56448 1278.28054)))
("SF_MASONRY_AND_ARCH" 0 ((16508.29751 1274.51075) (16455.50339 1277.98439) (16436.65158 1274.51075) (16414.02715
1278.27432) (16168.93100 1278.43518) (16157.61878 1281.89706) (16142.53394 1278.42828) (15897.43778 1278.27432)
(15878.58032 1274.51561) (15829.56448 1278.28054)))
("SF_PLANTING" 0 ((15829.56448 1029.41176) (15844.64367 1022.92025) (15859.72851 1021.86934)))
("SF_ARCHITECTURE" 0 ((15833.33145 5531.67421) (15833.48066 5463.80090) (15840.87477 5444.94762) (15840.87477
5245.09762) (15829.56256 5226.24434) (15833.33145 4177.97930)))
("SF_ARCHITECTURE" 0 ((15833.33145 5531.67421) (15863.34502 5540.41346) (15867.11482 5546.76380) (15866.06538
5580.54581) (15837.10407 5599.54751)))
("SF_PLANTING" 0 ((15833.33145 4177.97930) (15859.72851 4178.12715) (15889.89253 4191.86414) (15916.13631 4195.62183)
(15918.99751 4185.52036) (15893.66516 4147.81256)))
("SF_PLANTING" 0 ((15837.10407 4000.75373) (15833.33145 4012.06595)))
("SF_PLANTING" 0 ((15837.10407 4049.77376) (15833.33145 4012.06595)))
("SF_PLANTING" 0 ((15837.10407 4000.75373) (15833.33145 3985.67161)))
("SF_PLANTING" 0 ((15833.33145 1078.43043) (15844.64367 1089.74265)))
("SF_PLANTING" 0 ((15833.33145 788.08541) (15878.58032 791.85520)))
("SF_PLANTING" 0 ((15837.10407 7013.57466) (15859.72851 6990.95023)))
("SF_ARCHITECTURE" 0 ((15837.10407 5599.54751) (15863.33812 5633.48416) (15858.67217 5648.41912) (15840.87670
5659.87941)))
("SF_PLANTING" 0 ((15837.10407 4049.77376) (15837.10407 4091.25147)))
("SF_PLANTING" 0 ((15893.66516 4147.81256) (15871.04072 4146.75645) (15844.65204 4132.57545) (15837.25735 4121.41821)
(15837.10407 4091.25147)))
("SF_PLANTING" 0 ((15893.66516 4147.81256) (15892.60882 4132.73043) (15878.43394 4102.57059) (15859.72851 4092.30192)
(15837.10407 4091.25147)))
("SF_PLANTING" 0 ((15837.10407 4049.77376) (15855.95588 4049.77376)))
("SF_PLANTING" 0 ((15859.72851 4004.52489) (15837.10407 4000.75373)))
("SF_ARCHITECTURE" 0 ((15840.87670 5707.01357) (15840.87670 5723.98190)))
("SF_ARCHITECTURE" 0 ((16010.55995 5735.29412) (15855.95588 5731.36855) (15840.87670 5723.98190)))
("SF_ARCHITECTURE" 0 ((16010.55995 5735.29412) (16014.17364 5712.66968) (16003.01471 5701.51210) (15840.87670
5707.01357)))
("SF_ARCHITECTURE" 0 ((15840.87670 5707.01357) (15840.87670 5659.87941)))
("SF_PLANTING" 0 ((15961.53846 723.98190) (15938.91403 727.75170) (15848.42319 727.60464) (15840.87670 723.98190)))
("SF_MASONRY_AND_ARCH" 0 ((15874.81335 1904.22296) (15844.64367 1907.99423)))
("SF_MASONRY_AND_ARCH" 0 ((15844.64367 1907.99423) (15844.49729 1957.01357) (15840.88631 1972.09627) (15848.41629
2024.88688)))
("SF_PLANTING" 0 ((15852.18891 3808.44604) (15848.41629 3831.07048)))
("SF_PLANTING" 0 ((15897.43778 3868.77828) (15882.35294 3867.72851) (15867.27647 3861.08224) (15848.41629 3831.07048)))
("SF_MASONRY_AND_ARCH" 0 ((16074.66063 2028.65735) (16010.55995 2032.42172) (15995.47511 2028.80509) (15874.81335
2028.65113) (15848.41629 2024.88688)))
("SF_MASONRY_AND_ARCH" 0 ((16070.88801 1176.47059) (16059.57579 1172.84785) (15938.91403 1170.12681) (15855.96425
1172.84785) (15848.41629 1176.47059)))
("SF_PLANTING" 0 ((16025.63914 6772.24762) (16020.67217 6757.31244) (15999.24774 6742.23631) (15908.75000 6738.31753)
(15852.18891 6745.85192)))
("SF_PLANTING" 0 ((15855.95588 6779.78857) (15852.18891 6745.85192)))
("SF_PLANTING" 0 ((15852.18891 3808.44604) (15871.04072 3797.28224) (15927.60181 3799.02002)))
("SF_MASONRY_AND_ARCH" 0 ((15852.18891 2100.30192) (15859.73541 2103.92466) (15882.35294 2104.07240)))
("SF_MASONRY_AND_ARCH" 0 ((15976.62330 957.76776) (15867.26810 957.76776) (15856.11199 957.76776) (15852.18891
965.30826)))
("SF_PLANTING" 0 ((15855.95588 6779.78857) (15886.12557 6787.18201) (16006.78733 6787.33032)))
("SF_MASONRY_AND_ARCH" 0 ((15863.50113 1093.51527) (15904.97738 1097.28507) (15961.53846 1097.13733) (15976.62330
1093.51527)))
("SF_PLANTING" 0 ((15863.50113 403.47002) (15871.93416 395.92070) (15877.38450 377.07296) (15871.04072 335.59672)))
("SF_MASONRY_AND_ARCH" 0 ((15867.26810 1334.84163) (15957.76584 1332.26900) (15976.62330 1338.61143)))
("SF_PLANTING" 0 ((15867.26810 855.95871) (15912.51697 859.72229) (15946.45362 856.10577) (15980.39027 863.49830)))
("SF_PLANTING" 0 ((15871.04072 4049.77376) (15880.46946 4055.42986) (15882.35294 4049.77376) (15886.12557 4049.77376)))
("SF_MASONRY_AND_ARCH" 0 ((15878.58032 1749.62387) (15871.04072 1749.62387)))
("SF_MASONRY_AND_ARCH" 0 ((15871.04072 1380.09050) (15920.06222 1380.09050)))
("SF_PLANTING" 0 ((15871.04072 493.96776) (15878.44231 492.76290) (15907.69219 429.86425) (15908.89638 411.00962)
(15916.28959 392.15781)))
("SF_PLANTING" 0 ((15874.81335 512.81957) (15871.04072 493.96776)))
("SF_PLANTING" 0 ((15893.66516 335.59672) (15871.04072 335.59672)))
("SF_PLANTING" 0 ((15965.31109 6998.49197) (15938.91403 7003.31188) (15904.97738 7023.83088) (15874.81335 7024.88688)))
("SF_PLANTING" 0 ((15946.45362 6964.55532) (15893.66516 6994.87557) (15879.63812 7009.80419) (15874.81335 7024.88688)))
("SF_MASONRY_AND_ARCH" 0 ((15874.81335 3012.82025) (15874.95973 2971.34887) (15878.58032 2963.80090)))
("SF_MASONRY_AND_ARCH" 0 ((15886.12557 3141.02590) (15874.95973 3122.17195) (15874.81335 3012.82025)))
("SF_MASONRY_AND_ARCH" 0 ((15901.20475 3016.59152) (15874.81335 3012.82025)))
("SF_PLANTING" 0 ((15893.66516 6923.07692) (15878.58032 6968.32579)))
("SF_PLANTING" 0 ((15878.58032 3235.29412) (15901.20475 3235.29412)))
("SF_PLANTING" 0 ((15878.58032 3235.29412) (15874.81335 3220.21143) (15874.95973 3186.28100) (15878.58032 3178.73303)))
("SF_MASONRY_AND_ARCH" 0 ((15878.58032 3178.73303) (15897.43778 3178.73303)))
("SF_MASONRY_AND_ARCH" 0 ((15878.58032 3178.73303) (15874.96663 3156.10860) (15886.12557 3141.02590)))
("SF_MASONRY_AND_ARCH" 0 ((15901.20475 2963.80090) (15878.58032 2963.80090)))
("SF_PLANTING" 0 ((15961.53846 4015.83710) (15950.22624 4025.94514) (15935.14140 4027.00124) (15908.75000 4022.32274)
(15882.35294 4012.06595)))
("SF_PLANTING" 0 ((15901.20475 3944.19265) (15882.35294 3955.50486)))
("SF_PLANTING" 0 ((15912.51697 3981.90045) (15893.67206 3974.20441) (15882.35294 3955.50486)))
("SF_MASONRY_AND_ARCH" 0 ((15893.66516 3141.02590) (15886.12557 3141.02590)))
("SF_PLANTING" 0 ((15886.12557 554.29864) (15882.50622 565.61086) (15889.89253 607.08993)))
("SF_MASONRY_AND_ARCH" 0 ((15889.89253 1904.22296) (15897.44186 1900.60023) (15923.82919 1900.45249)))
("SF_PLANTING" 0 ((15893.66516 335.59672) (15895.33744 309.19966) (15883.77251 270.81176) (15889.89253 267.72342)))
("SF_PLANTING" 0 ((15893.66516 6923.07692) (15957.76584 6922.92862) (15976.62330 6919.30645) (15991.70249 6923.07692)))
("SF_MASONRY_AND_ARCH" 0 ((15893.66516 3141.02590) (15901.05147 3125.94242) (15904.97738 3054.29864) (15901.20475
3016.59152)))
("SF_MASONRY_AND_ARCH" 0 ((15893.66516 3141.02590) (15901.05147 3156.10860) (15897.43778 3178.73303)))
("SF_PLANTING" 0 ((15893.66516 335.59672) (15920.06222 350.67873)))
("SF_PLANTING" 0 ((15897.43778 3868.77828) (15905.13066 3849.92500) (15923.82919 3834.84163)))
("SF_PLANTING" 0 ((15897.43778 3868.77828) (15908.75000 3895.17387)))
("SF_PLANTING" 0 ((15901.20475 3235.29412) (15901.05837 3190.04525) (15897.43778 3178.73303)))
("SF_PLANTING" 0 ((15901.20475 3235.29412) (15916.28959 3239.06459) (15942.67828 3238.91686) (15950.22624 3235.29412)))
("SF_MASONRY_AND_ARCH" 0 ((15901.20475 3016.59152) (15904.97738 3001.50803) (15901.20475 2963.80090)))
("SF_MASONRY_AND_ARCH" 0 ((15901.20475 2963.80090) (15908.75407 2956.41380) (15938.91403 2956.40690) (15950.22624
2960.03043)))
("SF_PLANTING" 0 ((15901.20475 791.85520) (15912.51697 795.62014) (15976.62330 795.47794) (15991.70249 791.86143)
(16059.57579 792.00294) (16074.66063 795.62014) (16104.82466 793.05317) (16184.01018 799.39762) (16206.63462 795.63190)
(16315.98982 795.47794) (16327.30204 791.85520)))
("SF_PLANTING" 0 ((15908.75000 3914.02715) (15908.75000 3895.17387)))
("SF_PLANTING" 0 ((15908.75000 3914.02715) (15916.43733 3924.28269) (15927.60181 3928.81403) (15957.76584 3920.37093)
(15976.46719 3909.20679) (15980.39027 3902.71493)))
("SF_PLANTING" 0 ((15965.31109 3865.00713) (15953.99050 3882.66346) (15908.75000 3895.17387)))
("SF_ARCHITECTURE" 0 ((16157.61878 4464.55464) (15976.62330 4464.56154) (15953.99887 4468.32579) (15912.51697
4464.55464)))
("SF_PLANTING" 0 ((15987.93552 248.86878) (15953.99887 237.70498) (15923.82919 237.70430) (15912.51697 241.32636)))
("SF_PLANTING" 0 ((15931.37443 350.67873) (15931.22523 316.74208) (15922.78247 271.49321) (15912.51697 241.32636)))
("SF_ARCHITECTURE" 0 ((16176.47059 5625.94276) (16161.38575 5629.56516) (16010.55995 5629.71991) (15991.70249
5633.47760) (15931.37443 5633.33609) (15916.28959 5629.71335)))
("SF_PLANTING" 0 ((15916.28959 392.15781) (15935.14140 392.15781)))
("SF_PLANTING" 0 ((15916.28959 392.15781) (15920.06222 350.67873)))
("SF_MASONRY_AND_ARCH" 0 ((15927.60181 2111.61414) (15920.06222 2107.84287)))
("SF_PLANTING" 0 ((15931.37443 350.67873) (15920.06222 350.67873)))
("SF_ARCHITECTURE" 0 ((16168.93100 5588.23529) (15938.91403 5588.22907) (15923.82919 5584.46414)))
("SF_PLANTING" 0 ((15923.82919 3963.04717) (15942.68665 3966.81708)))
("SF_PLANTING" 0 ((15927.60181 3799.02002) (15923.97839 3808.37907) (15923.82919 3834.84163)))
("SF_PLANTING" 0 ((15953.99887 3849.92500) (15935.14140 3844.95622) (15923.82919 3834.84163)))
("SF_PLANTING" 0 ((15927.60181 3799.02002) (15932.42941 3774.50939) (15950.22624 3759.42726)))
("SF_PLANTING" 0 ((16010.55995 3793.36391) (15987.93552 3793.51176) (15950.22624 3800.75690) (15927.60181 3799.02002)))
("SF_MASONRY_AND_ARCH" 0 ((15927.60181 2111.61414) (15935.14977 2105.27036) (15965.31109 2103.01606) (16021.87217
2085.36697) (16217.94683 2088.98971)))
("SF_MASONRY_AND_ARCH" 0 ((15927.60181 2111.61414) (15927.74955 2130.46731) (15938.91403 2168.17523)))
("SF_PLANTING" 0 ((15927.60181 599.54751) (15950.22624 603.31731)))
("SF_MASONRY_AND_ARCH" 0 ((15931.37443 2439.66844) (15938.91403 2462.29287)))
("SF_MASONRY_AND_ARCH" 0 ((15931.37443 2398.19005) (15931.37443 2409.50226)))
("SF_MASONRY_AND_ARCH" 0 ((15931.37443 2398.19005) (15942.68665 2394.56731) (16018.09265 2394.27183) (16025.63914
2390.64830)))
("SF_PLANTING" 0 ((15931.37443 350.67873) (15946.45362 369.53337)))
("SF_PLANTING" 0 ((15935.14140 6847.66188) (15946.45362 6843.89796) (16010.55995 6844.94740) (16025.48586 6855.21018)
(16033.18439 6874.05758)))
("SF_PLANTING" 0 ((15957.76584 6889.14027) (15947.51143 6877.82805) (15935.14140 6847.66188)))
("SF_PLANTING" 0 ((15935.14140 392.15781) (15946.45362 369.53337)))
("SF_PLANTING" 0 ((15935.14140 392.15781) (15942.53054 403.47002) (15943.74163 429.86425) (15964.11109 463.80090)
(15965.31109 482.65554)))
("SF_MASONRY_AND_ARCH" 0 ((15965.31109 2462.29287) (15938.91403 2462.29287)))
("SF_MASONRY_AND_ARCH" 0 ((16036.95136 2496.22952) (16006.78733 2503.62274) (15946.45362 2502.56640) (15935.29751
2488.68778) (15938.91403 2462.29287)))
("SF_MASONRY_AND_ARCH" 0 ((15938.91403 2168.17523) (16044.49661 2168.18145) (16063.34842 2171.93880) (16123.68213
2168.18145) (16142.53394 2171.94570)))
("SF_MASONRY_AND_ARCH" 0 ((15938.91403 1896.68201) (15946.46199 1899.25452) (15961.53846 1892.91075)))
("SF_PLANTING" 0 ((15976.62330 380.84559) (15946.45362 369.53337)))
("SF_MASONRY_AND_ARCH" 0 ((15950.22624 2960.03043) (15946.45362 2982.65486) (15946.60283 3024.13247) (15950.21934
3039.21595) (15950.22624 3235.29412)))
("SF_PLANTING" 0 ((15950.22624 3235.29412) (15972.69740 3240.26878) (15976.46719 3246.61324) (15976.62138 3585.97285)))
("SF_MASONRY_AND_ARCH" 0 ((15950.22624 2756.41052) (15957.77421 2760.03326) (15999.24774 2760.18100)))
("SF_PLANTING" 0 ((15969.07805 584.46550) (15950.22624 603.31731)))
("SF_PLANTING" 0 ((15953.99887 614.62952) (15950.22624 603.31731)))
("SF_PLANTING" 0 ((15953.99887 3849.92500) (15961.53846 3846.15385)))
("SF_PLANTING" 0 ((15953.99887 3849.92500) (15965.31109 3865.00713)))
("SF_MASONRY_AND_ARCH" 0 ((15961.53846 1892.91075) (15957.76584 1877.82805)))
("SF_PLANTING" 0 ((15957.76584 629.71437) (15957.76584 641.02658) (15961.53846 644.79638)))
("SF_MASONRY_AND_ARCH" 0 ((16067.12104 1866.51584) (16066.96493 1889.13337) (16059.57172 1896.52738) (15976.62330
1896.67579) (15961.53846 1892.91075)))
("SF_PLANTING" 0 ((15965.31109 678.73303) (15961.53846 723.98190)))
("SF_PLANTING" 0 ((15961.53846 723.98190) (15980.39027 731.36900) (16003.01471 727.75928) (16044.49661 731.51742)
(16282.05317 731.52432)))
("SF_PLANTING" 0 ((15965.31109 6998.49197) (15972.85068 6994.72070)))
("SF_PLANTING" 0 ((16036.95136 7013.57466) (16025.63914 7017.50000) (15950.22624 7076.48631) (15927.75509 7080.24344)
(15923.98529 7073.89966) (15925.02919 7058.82353) (15965.31109 6998.49197)))
("SF_PLANTING" 0 ((16059.57579 3797.13382) (16048.11719 3826.25011) (15991.70249 3863.95102) (15965.31109 3865.00713)))
("SF_PLANTING" 0 ((15976.62330 3717.94830) (15965.31109 3729.26052)))
("SF_PLANTING" 0 ((15965.31109 527.90441) (15969.07805 584.46550)))
("SF_PLANTING" 0 ((15969.07805 584.46550) (16052.03620 584.61256) (16078.43326 592.00023) (16131.22172 591.85803)
(16142.53394 588.23529)))
("SF_PLANTING" 0 ((16063.34842 6938.15962) (16003.01471 6985.98857) (15972.85068 6994.72070)))
("SF_PLANTING" 0 ((15991.70249 6923.07692) (15986.88462 6941.93088) (15970.12896 6975.86753) (15972.85068 6994.72070)))
("SF_MASONRY_AND_ARCH" 0 ((15976.62330 1470.58824) (15972.85068 1478.13066)))
("SF_MASONRY_AND_ARCH" 0 ((15972.85068 1376.32070) (15976.47410 1368.77138) (15976.62330 1338.61143)))
("SF_MASONRY_AND_ARCH" 0 ((16104.82466 1029.41176) (16070.88801 1025.64197) (16063.34842 1025.64197) (16040.72398
1029.11561) (16014.32692 1025.78903) (15999.24774 1029.25713) (15980.39027 1024.43710) (15970.28360 1014.32975)
(15972.85068 999.24491)))
("SF_PLANTING" 0 ((15976.62330 3717.94830) (15976.62138 3585.97285)))
("SF_ARCHITECTURE" 0 ((17202.10973 3589.74333) (16926.84955 3589.73710) (16904.22511 3585.97285) (16843.89140
3586.12059) (16828.80656 3589.73710) (16530.92195 3589.73710) (16508.29751 3585.97285) (16444.19118 3586.12059)
(16429.11199 3589.73710) (16165.15837 3589.73710) (16146.30656 3585.97907) (15976.62138 3585.97285)))
("SF_ARCHITECTURE" 0 ((15999.24774 5848.41629) (16017.04321 5874.81154) (16017.04321 5908.74785) (16010.40939
5918.86256) (15976.62330 5923.83100)))
("SF_PLANTING" 0 ((15991.70249 3725.49061) (15984.16290 3725.49061) (15976.62330 3717.94830)))
("SF_MASONRY_AND_ARCH" 0 ((15976.62330 1440.42138) (15976.62330 1414.02715)))
("SF_MASONRY_AND_ARCH" 0 ((16184.01018 1334.84163) (16010.55995 1334.84785) (15976.62330 1338.61143)))
("SF_MASONRY_AND_ARCH" 0 ((15976.62330 1093.51527) (15976.62330 1067.11821)))
("SF_MASONRY_AND_ARCH" 0 ((15976.62330 1093.51527) (15995.47511 1097.27885) (16059.57579 1095.61346) (16082.20023
1101.05486)))
("SF_MASONRY_AND_ARCH" 0 ((16285.82014 957.76776) (16270.74095 957.76776) (16018.09955 957.76776) (16010.55995
957.76776) (15976.62330 957.76776)))
("SF_MASONRY_AND_ARCH" 0 ((15976.62330 946.45645) (15976.62330 957.76776)))
("SF_MASONRY_AND_ARCH" 0 ((15980.39027 863.49830) (15976.76968 871.04762) (15976.62330 912.51980)))
("SF_PLANTING" 0 ((15976.62330 380.84559) (16006.78733 380.84559)))
("SF_PLANTING" 0 ((15976.62330 380.84559) (15977.67828 407.23982) (15991.70249 429.86425)))
("SF_PLANTING" 0 ((15980.39027 6583.71041) (15984.16290 6587.48088) (15995.47511 6587.48088)))
("SF_MASONRY_AND_ARCH" 0 ((16082.20023 2850.67873) (16077.37545 2831.83167) (16059.57579 2821.56278) (15991.70249
2820.36482) (15980.39027 2816.74208)))
("SF_MASONRY_AND_ARCH" 0 ((15980.39027 1749.62387) (15991.70249 1749.62387)))
("SF_PLANTING" 0 ((15980.39027 863.49830) (15995.47511 860.02466) (16010.55995 863.49830)))
("SF_PLANTING" 0 ((15987.93552 248.86878) (16010.55995 233.93450) (16052.03620 233.93382) (16063.34842 237.55656)))
("SF_PLANTING" 0 ((15987.93552 248.86878) (15988.99050 263.94593) (15995.47511 271.49321)))
("SF_PLANTING" 0 ((16029.41176 6900.45249) (16010.70633 6901.65679) (15999.10407 6919.15158) (15991.70249 6923.07692)))
("SF_PLANTING" 0 ((15991.70249 3725.49061) (16010.55995 3717.94830)))
("SF_PLANTING" 0 ((16010.55995 3793.36391) (16016.89536 3755.65611) (16010.40939 3744.49853) (15995.62839 3736.64785)
(15991.70249 3725.49061)))
("SF_PLANTING" 0 ((15991.70249 429.86425) (16003.01471 428.65939) (16014.32692 418.55204)))
("SF_PLANTING" 0 ((15991.70249 429.86425) (15989.13133 444.94627) (15992.89559 456.25848) (16003.16391 469.99005)
(16014.32692 467.57070)))
("SF_PLANTING" 0 ((16033.18439 6568.62771) (15995.47511 6587.48088)))
("SF_PLANTING" 0 ((15999.24774 6598.79310) (15995.47511 6587.48088)))
("SF_PLANTING" 0 ((15995.47511 271.49321) (16003.01471 305.42986)))
("SF_PLANTING" 0 ((16048.26357 309.19966) (16033.03382 276.32014) (16021.87217 271.64163) (15995.47511 271.49321)))
("SF_PLANTING" 0 ((16003.01471 6527.14932) (15999.39412 6519.60102) (15999.24774 6485.67127)))
("SF_PLANTING" 0 ((15999.24774 6485.67127) (16078.43326 6487.77715) (16089.74548 6493.21267)))
("SF_ARCHITECTURE" 0 ((15999.24774 5848.41629) (16017.95181 5818.25045) (16016.89536 5799.39661) (16006.78733
5784.31380)))
("SF_MASONRY_AND_ARCH" 0 ((15999.24774 2760.18100) (15999.24774 2782.80543)))
("SF_MASONRY_AND_ARCH" 0 ((16067.12104 2760.18100) (16040.72398 2756.41052) (15999.24774 2760.18100)))
("SF_PLANTING" 0 ((16036.95136 6677.97862) (16006.78733 6663.94570) (15995.63665 6664.10045) (15992.90803 6670.44423)
(16003.01471 6700.60305)))
("SF_MASONRY_AND_ARCH" 0 ((16003.01471 3174.96256) (16025.63914 3186.12704) (16070.88801 3186.12704) (16082.20023
3182.79977) (16097.28507 3186.26855) (16202.86765 3186.27477)))
("SF_PLANTING" 0 ((16003.01471 305.42986) (16007.84367 328.05430) (16021.87217 358.22115)))
("SF_PLANTING" 0 ((16048.26357 309.19966) (16003.01471 305.42986)))
("SF_PLANTING" 0 ((16025.63914 6772.24762) (16010.71324 6780.83846) (16006.78733 6787.33032)))
("SF_PLANTING" 0 ((16006.78733 6787.33032) (16018.09955 6806.18428)))
("SF_ARCHITECTURE" 0 ((16010.55995 5735.29412) (16014.18054 5742.84208) (16014.18054 5769.23077) (16006.78733
5784.31380)))
("SF_MASONRY_AND_ARCH" 0 ((16006.78733 3137.25464) (16018.09955 3126.09706) (16070.88801 3122.32658) (16082.20023
3129.71369)))
("SF_PLANTING" 0 ((16021.87217 358.22115) (16006.78733 380.84559)))
("SF_PLANTING" 0 ((16014.32692 418.55204) (16006.78733 380.84559)))
("SF_PLANTING" 0 ((16010.55995 3793.36391) (16018.10645 3796.98597) (16059.57579 3797.13382)))
("SF_MASONRY_AND_ARCH" 0 ((16010.55995 2450.98066) (16036.95136 2450.98066)))
("SF_MASONRY_AND_ARCH" 0 ((16014.32692 3042.98643) (16029.41176 3042.98643)))
("SF_PLANTING" 0 ((16101.05769 448.71889) (16074.66063 443.89751) (16036.95136 423.37896) (16014.32692 418.55204)))
("SF_PLANTING" 0 ((16018.09955 3898.94378) (16044.49661 3891.40271)))
("SF_MASONRY_AND_ARCH" 0 ((16021.87217 2311.46278) (16025.63914 2300.15057)))
("SF_PLANTING" 0 ((16070.88801 373.30317) (16021.87217 358.22115)))
("SF_PLANTING" 0 ((16025.63914 6772.24762) (16044.49661 6772.39548) (16089.74548 6785.44468)))
("SF_MASONRY_AND_ARCH" 0 ((16172.69796 2971.34265) (16025.63914 2971.34265)))
("SF_MASONRY_AND_ARCH" 0 ((16025.63914 2907.23982) (16033.18846 2899.85271) (16074.59016 2899.47919) (16085.52274
2895.77296) (16142.53394 2903.46934) (16206.63462 2903.32161) (16225.49208 2899.69808) (16308.44457 2903.46312)
(16346.15385 2895.92760)))
("SF_MASONRY_AND_ARCH" 0 ((16025.63914 2349.17070) (16025.63914 2390.64830)))
("SF_MASONRY_AND_ARCH" 0 ((16138.76131 2394.41957) (16127.44910 2398.04231) (16044.49661 2398.18382) (16025.63914
2390.64830)))
("SF_MASONRY_AND_ARCH" 0 ((16078.43326 1421.56957) (16025.63914 1417.79695)))
("SF_PLANTING" 0 ((16029.41176 6900.45249) (16033.18439 6874.05758)))
("SF_PLANTING" 0 ((16063.34842 6938.15962) (16050.97986 6915.68348) (16029.41176 6900.45249)))
("SF_PLANTING" 0 ((16029.41176 3469.08020) (16044.49661 3472.70294) (16085.97285 3472.85068)))
("SF_MASONRY_AND_ARCH" 0 ((16029.41176 1670.43744) (16059.57579 1670.43744) (16082.20023 1670.43744) (16161.38575
1670.43744) (16176.47059 1670.43744) (16214.17986 1670.43744)))
("SF_MASONRY_AND_ARCH" 0 ((16029.41176 1670.43744) (16029.41176 1640.27149)))
("SF_PLANTING" 0 ((16033.18439 6874.05758) (16085.97285 6873.90928) (16101.05769 6870.28631)))
("SF_PLANTING" 0 ((16033.18439 6568.62771) (16033.33767 6606.32828) (16037.10192 6612.67229) (16044.49661 6613.87658)))
("SF_PLANTING" 0 ((16033.18439 6568.62771) (16048.11719 6573.59593) (16054.75102 6583.71041) (16054.75792 6595.02262)
(16044.49661 6613.87658)))
("SF_PLANTING" 0 ((16059.57579 3536.95351) (16033.18439 3536.95351)))
("SF_MASONRY_AND_ARCH" 0 ((16127.44910 1602.56505) (16044.49661 1601.04672) (16033.18439 1610.10464)))
("SF_PLANTING" 0 ((16059.57579 859.72851) (16033.18439 855.95871)))
("SF_PLANTING" 0 ((16036.95136 6677.97862) (16052.03620 6677.97862)))
("SF_PLANTING" 0 ((16036.95136 6677.97862) (16033.33077 6685.52692) (16034.38710 6704.22602) (16048.26357 6711.91527)))
("SF_ARCHITECTURE" 0 ((16036.95136 3646.30509) (16048.26357 3650.06878) (17205.88235 3650.08190) (17217.19457
3653.84615)))
("SF_MASONRY_AND_ARCH" 0 ((16036.95136 3337.10407) (16052.03620 3340.87455) (16082.20023 3337.10407) (16108.59729
3340.86833) (16187.78281 3340.86833) (16199.09502 3337.10407)))
("SF_MASONRY_AND_ARCH" 0 ((16036.95136 2496.22952) (16036.95136 2450.98066)))
("SF_MASONRY_AND_ARCH" 0 ((16089.74548 2507.54174) (16063.34842 2496.38416) (16036.95136 2496.22952)))
("SF_MASONRY_AND_ARCH" 0 ((16055.80882 2443.43891) (16048.25950 2449.78269) (16036.95136 2450.98066)))
("SF_PLANTING" 0 ((16153.84615 3265.46029) (16112.36991 3269.22387) (16085.97285 3265.60871) (16048.27195 3272.70509)
(16040.72398 3269.23077)))
("SF_MASONRY_AND_ARCH" 0 ((16048.26357 1738.31165) (16040.87726 1745.85882) (16040.72398 1768.47568)))
("SF_PLANTING" 0 ((16059.57579 6647.81324) (16044.49661 6613.87658)))
("SF_PLANTING" 0 ((16052.03620 6677.97862) (16055.65271 6693.06210) (16048.26357 6711.91527)))
("SF_PLANTING" 0 ((16048.26357 6711.91527) (16049.46357 6723.22783) (16059.72636 6737.10667) (16085.97285 6738.31097)))
("SF_PLANTING" 0 ((16048.26357 309.19966) (16070.88801 316.74208)))
("SF_PLANTING" 0 ((16052.03620 7021.11640) (16053.24038 7006.03292) (16067.12104 6990.95023)))
("SF_PLANTING" 0 ((16059.57579 6647.81324) (16053.09253 6662.89593) (16052.03620 6677.97862)))
("SF_PLANTING" 0 ((16055.80882 7062.59400) (16078.43326 7044.93179) (16101.05769 7039.96957)))
("SF_ARCHITECTURE" 0 ((16055.80882 3710.40724) (16131.22172 3717.94208) (17224.73416 3717.95520) (17236.04638
3721.71946)))
("SF_PLANTING" 0 ((16089.74548 6647.81324) (16059.57579 6647.81324)))
("SF_ARCHITECTURE" 0 ((16059.57579 3797.13382) (16078.43326 3793.36391) (16210.40724 3793.37014) (16229.25905
3797.13382)))
("SF_PLANTING" 0 ((16059.57579 769.23077) (16063.34842 761.68835)))
("SF_PLANTING" 0 ((16063.34842 6938.15962) (16078.43326 6941.93088)))
("SF_PLANTING" 0 ((16138.76131 248.86878) (16116.13688 233.93450) (16070.89638 233.93382) (16063.34842 237.55656)))
("SF_PLANTING" 0 ((16063.34842 237.55656) (16074.66063 271.49321)))
("SF_MASONRY_AND_ARCH" 0 ((16270.74095 3046.75690) (16214.17986 3042.98643) (16168.93100 3046.75068) (16146.30656
3044.03586) (16108.59729 3046.60226) (16097.28507 3043.28258) (16082.20023 3046.60226) (16067.12104 3042.98643)))
("SF_MASONRY_AND_ARCH" 0 ((16067.12104 2760.18100) (16067.12104 2771.49321)))
("SF_MASONRY_AND_ARCH" 0 ((16342.38122 2760.18100) (16315.98982 2756.41052) (16225.49208 2760.17477) (16153.84615
2753.83722) (16067.12104 2760.18100)))
("SF_MASONRY_AND_ARCH" 0 ((16184.01018 1866.51584) (16067.12104 1866.51584)))
("SF_MASONRY_AND_ARCH" 0 ((16070.88801 1176.47059) (16070.88801 1184.01301)))
("SF_MASONRY_AND_ARCH" 0 ((16070.88801 1176.47059) (16088.53993 1165.01063) (16089.74548 1134.99152)))
("SF_PLANTING" 0 ((16070.88801 373.30317) (16119.90950 373.30317)))
("SF_PLANTING" 0 ((16070.88801 373.30317) (16070.88801 316.74208)))
("SF_PLANTING" 0 ((16085.97285 316.74208) (16070.88801 316.74208)))
("SF_ARCHITECTURE" 0 ((16074.66063 5833.33326) (16089.74548 5829.56267) (16168.93100 5829.71086) (16187.78281
5833.33326) (16221.71946 5829.56923) (16734.54186 5829.56923) (16757.16629 5833.33326) (16832.57919 5833.18507)
(16847.66403 5829.56923) (17168.17308 5829.56923) (17179.48529 5833.33326)))
("SF_ARCHITECTURE" 0 ((16074.66063 5799.39661) (16089.74548 5795.62590) (16187.78281 5795.62590) (16199.09502
5795.62590) (16217.94683 5795.62590) (16738.30882 5795.62590) (16760.93326 5795.62590) (16783.55769 5795.92229)
(16828.80656 5799.39661) (16851.43100 5795.63258) (17119.15724 5795.63258) (17134.23643 5799.24842) (17160.63348
5795.92229) (17183.25792 5799.39661)))
("SF_ARCHITECTURE" 0 ((16168.93100 5712.66968) (16134.99434 5708.90543) (16082.20860 5712.37353) (16074.66063
5708.89887)))
("SF_MASONRY_AND_ARCH" 0 ((16074.66063 2028.65735) (16074.66063 2021.11640)))
("SF_MASONRY_AND_ARCH" 0 ((16101.05769 2036.19910) (16074.66063 2028.65735)))
("SF_PLANTING" 0 ((16078.43326 6941.93088) (16112.36991 6934.53744) (16146.29819 6934.53744) (16153.84615 6938.15962)))
("SF_PLANTING" 0 ((16082.20023 6964.55532) (16078.43326 6941.93088)))
("SF_PLANTING" 0 ((16078.43326 6417.79796) (16089.74548 6447.96380)))
("SF_PLANTING" 0 ((16078.43326 6334.84163) (16089.74548 6353.69525)))
("SF_MASONRY_AND_ARCH" 0 ((16078.43326 1930.61867) (16097.27817 1927.00204) (16104.82466 1934.38914)))
("SF_MASONRY_AND_ARCH" 0 ((16082.20023 3080.69355) (16082.20023 3088.23529)))
("SF_MASONRY_AND_ARCH" 0 ((16112.36991 1983.40848) (16082.20023 1987.17975)))
("SF_MASONRY_AND_ARCH" 0 ((16312.21719 1078.43043) (16297.13235 1082.19615) (16176.47059 1082.19615) (16157.61878
1078.58575) (16138.76131 1082.20305) (16115.45758 1078.80611) (16108.44400 1092.31663) (16082.20023 1101.05486)))
("SF_MASONRY_AND_ARCH" 0 ((16082.20023 1101.05486) (16082.35633 1123.67930) (16089.74548 1134.99152)))
("SF_PLANTING" 0 ((16093.51244 6719.45701) (16085.97285 6738.31097)))
("SF_PLANTING" 0 ((16089.74548 6785.44468) (16085.97285 6738.31097)))
("SF_PLANTING" 0 ((16085.97285 316.74208) (16097.29197 294.26606) (16134.99434 275.26301)))
("SF_PLANTING" 0 ((16085.97285 316.74208) (16097.28507 324.12919) (16131.22172 328.05430)))
("SF_PLANTING" 0 ((16138.76131 6779.78857) (16108.59729 6779.93688) (16089.74548 6785.44468)))
("SF_PLANTING" 0 ((16089.74548 6785.44468) (16089.89186 6825.03744) (16101.05769 6870.28631)))
("SF_PLANTING" 0 ((16089.74548 6685.52036) (16093.51244 6719.45701)))
("SF_PLANTING" 0 ((16089.74548 6647.81324) (16127.44910 6647.81324)))
("SF_PLANTING" 0 ((16089.74548 6647.81324) (16089.89876 6621.41787) (16097.29197 6612.35950) (16126.24638 6617.80192)
(16127.44910 6647.81324)))
("SF_PLANTING" 0 ((16121.79299 6487.55656) (16089.74548 6493.21267)))
("SF_PLANTING" 0 ((16093.51244 6508.29570) (16093.51244 6496.98348) (16089.74548 6493.21267)))
("SF_MASONRY_AND_ARCH" 0 ((16168.93100 1127.45192) (16089.74548 1134.99152)))
("SF_PLANTING" 0 ((16116.13688 6719.45701) (16093.51244 6719.45701)))
("SF_MASONRY_AND_ARCH" 0 ((16093.51244 3536.95351) (16108.59729 3536.95351)))
("SF_PLANTING" 0 ((16191.55543 859.72851) (16093.51244 859.72851)))
("SF_PLANTING" 0 ((16097.28507 6557.31550) (16123.68213 6557.31550)))
("SF_MASONRY_AND_ARCH" 0 ((16693.05995 3469.07998) (16670.43552 3469.07998) (16598.79525 3469.07998) (16561.08597
3469.07998) (16546.00113 3469.07998) (16515.83710 3476.61493) (16459.27602 3472.85068) (16285.82014 3472.85690)
(16270.74095 3476.32500) (16259.42873 3473.00532) (16172.69796 3472.85690) (16157.61878 3476.47342) (16116.13688
3476.61493) (16097.28507 3472.85068)))
("SF_MASONRY_AND_ARCH" 0 ((16097.28507 2582.95600) (16079.63597 2575.26041) (16078.57964 2564.10283) (16083.25803
2552.79683) (16089.74955 2546.45305) (16123.68213 2541.47839)))
("SF_PLANTING" 0 ((16101.05769 7024.88688) (16101.05769 7039.96957)))
("SF_PLANTING" 0 ((16138.76131 7058.82353) (16119.76176 7092.60532) (16101.21097 7098.04774) (16097.29197 7088.98937)
(16103.62885 7047.51787) (16101.05769 7039.96957)))
("SF_PLANTING" 0 ((16101.05769 7024.88688) (16127.44910 7019.91210) (16145.24876 7002.26244) (16157.46267 6979.63801)
(16153.84615 6953.24310)))
("SF_PLANTING" 0 ((16101.05769 7024.88688) (16101.05769 7006.03292)))
("SF_PLANTING" 0 ((16123.68213 6975.86753) (16118.70532 6994.57319) (16101.05769 7006.03292)))
("SF_PLANTING" 0 ((16123.68213 6975.86753) (16116.13281 6973.29400) (16104.82466 6976.01538) (16094.71799 6983.41538)
(16094.57025 6998.48507) (16101.05769 7006.03292)))
("SF_PLANTING" 0 ((16146.30656 6874.05758) (16101.05769 6870.28631)))
("SF_MASONRY_AND_ARCH" 0 ((16210.40724 2024.88688) (16191.55543 2032.28088) (16108.60419 2032.57636) (16101.05769
2036.19910)))
("SF_MASONRY_AND_ARCH" 0 ((16104.82466 2051.28179) (16101.05769 2047.51131) (16101.05769 2036.19910)))
("SF_PLANTING" 0 ((16101.05769 448.71889) (16112.36991 448.71889) (16116.13688 452.48869)))
("SF_PLANTING" 0 ((16101.05769 448.71889) (16102.26041 418.55204) (16112.36991 407.39446) (16127.29581 399.55034)
(16131.22172 392.15781)))
("SF_MASONRY_AND_ARCH" 0 ((16104.82466 1029.41176) (16112.36991 1025.64197)))
("SF_MASONRY_AND_ARCH" 0 ((16104.82466 1029.41176) (16108.59729 1040.72398)))
("SF_PLANTING" 0 ((16112.36991 6297.13416) (16116.13688 6266.96833)))
("SF_MASONRY_AND_ARCH" 0 ((16293.36538 2507.54174) (16191.55543 2500.00622) (16112.36991 2503.77048)))
("SF_MASONRY_AND_ARCH" 0 ((16112.36991 1972.09627) (16112.36991 1983.40848)))
("SF_MASONRY_AND_ARCH" 0 ((16112.36991 1983.40848) (16142.53394 1990.80249) (16187.78281 1987.18597) (16206.63462
1990.95023)))
("SF_MASONRY_AND_ARCH" 0 ((16112.36991 1172.70079) (16229.25905 1172.84853) (16244.34389 1180.24038)))
("SF_PLANTING" 0 ((16127.44910 6696.83258) (16116.13688 6719.45701)))
("SF_PLANTING" 0 ((16116.13688 6719.45701) (16134.99434 6734.53971)))
("SF_PLANTING" 0 ((16121.79299 6487.55656) (16116.15622 6474.36222) (16126.25328 6444.19299) (16120.20645 6425.33937)
(16123.38518 6414.02715) (16120.06278 6376.31968) (16127.59966 6361.39163) (16145.10656 6349.91810) (16149.91335
6331.07738) (16142.52704 6323.83213) (16116.13688 6331.07081)))
("SF_PLANTING" 0 ((16119.90950 6206.63643) (16119.90950 6236.80249)))
("SF_PLANTING" 0 ((16131.22172 328.05430) (16131.06844 350.67873) (16119.90950 373.30317)))
("SF_PLANTING" 0 ((16131.22172 392.15781) (16119.90950 373.30317)))
("SF_PLANTING" 0 ((16121.79299 6487.55656) (16126.25328 6546.00294) (16123.68213 6557.31550)))
("SF_PLANTING" 0 ((16121.79299 6487.55656) (16150.07353 6489.44186)))
("SF_PLANTING" 0 ((16123.68213 6975.86753) (16153.84615 6953.24310)))
("SF_PLANTING" 0 ((16123.68213 6564.85645) (16123.68213 6576.16867)))
("SF_PLANTING" 0 ((16123.68213 6564.85645) (16123.68213 6557.31550)))
("SF_PLANTING" 0 ((16123.68213 6564.85645) (16157.61878 6572.39819)))
("SF_PLANTING" 0 ((16127.44910 6696.83258) (16168.93100 6693.20995) (16187.78281 6698.03688) (16202.86765 6711.91527)))
("SF_PLANTING" 0 ((16127.44910 6696.83258) (16123.68213 6677.97862) (16127.44910 6647.81324)))
("SF_PLANTING" 0 ((16127.44910 6647.81324) (16142.53394 6646.76301) (16157.61878 6640.11663) (16175.41425 6621.41753)
(16181.43903 6598.94796) (16187.78281 6595.02262)))
("SF_PLANTING" 0 ((16146.30656 392.15781) (16131.22172 392.15781)))
("SF_PLANTING" 0 ((16150.07353 320.51188) (16131.22172 328.05430)))
("SF_PLANTING" 0 ((16202.86765 6711.91527) (16195.31833 6723.07998) (16184.01018 6729.71324) (16134.99434 6734.53971)))
("SF_PLANTING" 0 ((16138.76131 6779.78857) (16134.99434 6734.53971)))
("SF_PLANTING" 0 ((16138.76131 248.86878) (16134.99434 275.26301)))
("SF_PLANTING" 0 ((16150.07353 320.51188) (16141.33812 282.81233) (16134.99434 275.26301)))
("SF_PLANTING" 0 ((16138.76131 6779.78857) (16150.07353 6779.78857) (16153.84615 6783.55984)))
("SF_MASONRY_AND_ARCH" 0 ((16138.76131 2239.81900) (16142.53394 2266.21391)))
("SF_PLANTING" 0 ((16167.04186 246.98247) (16138.76131 248.86878)))
("SF_MASONRY_AND_ARCH" 0 ((16142.53394 2266.21391) (16150.08190 2269.83744) (16236.80430 2270.13292) (16251.88348
2273.74943) (16304.67760 2269.98518) (16353.69344 2270.13292) (16365.00566 2273.45950) (16383.86312 2269.99208)
(16402.71493 2273.60102) (16440.42421 2269.98518)))
("SF_MASONRY_AND_ARCH" 0 ((16195.32240 2168.17523) (16153.84615 2168.32296) (16142.53394 2171.94570)))
("SF_MASONRY_AND_ARCH" 0 ((16221.71946 2183.25792) (16210.40724 2190.64502) (16172.69796 2194.27398) (16150.22964
2189.59548) (16142.53394 2171.94570)))
("SF_PLANTING" 0 ((16146.30656 6874.05758) (16153.85305 6867.70701) (16187.78281 6858.97410)))
("SF_PLANTING" 0 ((16146.30656 6874.05758) (16156.56097 6896.68201) (16161.38575 6923.07692)))
("SF_PLANTING" 0 ((16146.30656 456.25848) (16153.84615 456.25848)))
("SF_PLANTING" 0 ((16146.30656 392.15781) (16157.61878 388.39208) (16191.55543 392.00939) (16210.40724 383.55905)
(16248.10814 350.67873) (16285.97070 305.58450) (16308.44457 294.11765)))
("SF_PLANTING" 0 ((16146.30656 392.15781) (16157.46957 418.55204) (16153.84615 456.25848)))
("SF_PLANTING" 0 ((16251.88348 6489.44186) (16236.80430 6485.67127) (16157.62285 6485.81946) (16150.07353 6489.44186)))
("SF_PLANTING" 0 ((16150.07353 6489.44186) (16161.09163 6530.91980) (16157.61878 6542.23201)))
("SF_MASONRY_AND_ARCH" 0 ((16150.07353 2647.05882) (16150.07353 2722.47387)))
("SF_MASONRY_AND_ARCH" 0 ((16150.07353 2647.05882) (16308.44050 2647.21346) (16314.93891 2650.98394) (16323.52941
2665.91278)))
("SF_MASONRY_AND_ARCH" 0 ((16150.07353 2601.80995) (16293.36538 2598.03948)))
("SF_PLANTING" 0 ((16150.07353 320.51188) (16176.46369 331.97251) (16184.01018 346.90894)))
("SF_PLANTING" 0 ((16153.84615 6953.24310) (16153.84615 6938.15962)))
("SF_PLANTING" 0 ((16161.38575 6923.07692) (16160.18993 6934.23428) (16153.84615 6938.15962)))
("SF_PLANTING" 0 ((16206.63462 6783.55984) (16153.84615 6783.55984)))
("SF_PLANTING" 0 ((16187.78281 6832.57919) (16162.44355 6809.95475) (16153.84615 6783.55984)))
("SF_MASONRY_AND_ARCH" 0 ((16176.47059 2398.19005) (16153.84615 2394.41957)))
("SF_PLANTING" 0 ((16161.38575 467.57070) (16153.84615 463.80090) (16153.84615 456.25848)))
("SF_ARCHITECTURE" 0 ((16172.69796 4453.24242) (16157.61878 4464.55464)))
("SF_ARCHITECTURE" 0 ((16157.61878 4464.55464) (16168.93100 4479.63801)))
("SF_PLANTING" 0 ((16210.40724 6911.76471) (16191.55543 6919.15814) (16161.38575 6923.07692)))
("SF_PLANTING" 0 ((16167.04186 246.98247) (16195.32240 244.04186) (16206.63462 233.78676)))
("SF_PLANTING" 0 ((16167.04186 246.98247) (16172.85124 233.78880) (16184.01018 223.67794) (16195.32240 223.53020)
(16206.63462 233.78676)))
("SF_PLANTING" 0 ((16167.04186 246.98247) (16169.15600 256.34287) (16187.78281 279.03563)))
("SF_PLANTING" 0 ((16195.32240 7009.80419) (16187.77590 7011.00848) (16176.47749 7021.11640) (16168.93100 7036.19910)))
("SF_PLANTING" 0 ((16172.69796 6406.48575) (16168.93100 6414.02715)))
("SF_PLANTING" 0 ((16248.11652 7126.69683) (16240.56719 7140.56867) (16229.26742 7137.85419) (16176.47059 7062.59400)))
("SF_PLANTING" 0 ((16184.01018 346.90894) (16180.24321 358.22115)))
("SF_MASONRY_AND_ARCH" 0 ((16184.01018 1334.84163) (16195.32240 1331.07183)))
("SF_MASONRY_AND_ARCH" 0 ((16184.01018 1334.84163) (16187.78281 1346.15385)))
("SF_PLANTING" 0 ((16289.59276 252.63857) (16217.94683 335.44830) (16206.63462 342.08066) (16184.01018 346.90894)))
("SF_PLANTING" 0 ((16187.78281 6858.97410) (16187.78281 6832.57919)))
("SF_PLANTING" 0 ((16206.63462 6862.74536) (16187.78281 6858.97410)))
("SF_PLANTING" 0 ((16206.63462 6783.55984) (16196.38020 6806.18428) (16194.12658 6828.65385) (16187.78281 6832.57919)))
("SF_MASONRY_AND_ARCH" 0 ((16187.78281 1421.56957) (16221.71946 1421.56957)))
("SF_MASONRY_AND_ARCH" 0 ((16187.78281 1127.45192) (16214.17986 1116.13971)))
("SF_MASONRY_AND_ARCH" 0 ((16199.09502 3269.23077) (16191.55543 3265.46029)))
("SF_PLANTING" 0 ((16191.55543 859.72851) (16285.82014 859.72229) (16304.67760 855.95871)))
("SF_PLANTING" 0 ((16191.55543 859.72851) (16191.55543 829.56165)))
("SF_PLANTING" 0 ((16195.32240 7009.80419) (16195.32240 6998.49197) (16199.09502 6994.72070)))
("SF_PLANTING" 0 ((16195.32240 7009.80419) (16233.03167 7028.65735)))
("SF_MASONRY_AND_ARCH" 0 ((16199.09502 3269.23077) (16199.09502 3299.39695)))
("SF_MASONRY_AND_ARCH" 0 ((16199.09502 3269.23077) (16206.63462 3254.14808)))
("SF_MASONRY_AND_ARCH" 0 ((16206.63462 3254.14808) (16199.09502 3220.21143)))
("SF_MASONRY_AND_ARCH" 0 ((16199.09502 3205.12794) (16202.86765 3186.27477)))
("SF_MASONRY_AND_ARCH" 0 ((16199.09502 1602.56505) (16221.71946 1610.09842) (16327.30204 1610.09977) (16342.38122
1606.33484)))
("SF_PLANTING" 0 ((16210.40724 6711.91527) (16202.86765 6711.91527)))
("SF_MASONRY_AND_ARCH" 0 ((16202.86765 3386.12342) (16206.79072 3397.42941) (16217.94683 3404.82274) (16274.50792
3412.51290) (16327.30204 3408.74785)))
("SF_MASONRY_AND_ARCH" 0 ((16327.30204 3193.81572) (16278.28054 3186.42251) (16202.86765 3186.27477)))
("SF_MASONRY_AND_ARCH" 0 ((16202.86765 1866.51584) (16233.03167 1862.74536)))
("SF_MASONRY_AND_ARCH" 0 ((16210.40724 1542.23133) (16210.25950 1564.85577) (16202.86765 1583.71041)))
("SF_PLANTING" 0 ((16206.63462 6862.74536) (16240.57127 6862.74536)))
("SF_PLANTING" 0 ((16206.63462 6862.74536) (16210.25950 6874.05758) (16210.40724 6911.76471)))
("SF_PLANTING" 0 ((16214.17986 6764.70588) (16206.63462 6783.55984)))
("SF_MASONRY_AND_ARCH" 0 ((16414.02715 3254.14808) (16349.92647 3254.29581) (16338.61425 3257.76391) (16319.75679
3254.15498) (16259.42873 3254.29581) (16244.34389 3257.76391) (16206.63462 3254.14808)))
("SF_MASONRY_AND_ARCH" 0 ((16259.42873 2971.34265) (16251.87941 2967.71912) (16206.63462 2967.57138)))
("SF_MASONRY_AND_ARCH" 0 ((16349.92647 1987.17975) (16225.49208 1987.18597) (16206.63462 1990.95023)))
("SF_MASONRY_AND_ARCH" 0 ((16210.40724 2024.88688) (16206.63462 1990.95023)))
("SF_PLANTING" 0 ((16206.63462 471.34333) (16229.25905 467.57070)))
("SF_PLANTING" 0 ((16206.63462 233.78676) (16233.03167 237.55656)))
("SF_PLANTING" 0 ((16236.80430 6924.96256) (16210.40724 6911.76471)))
("SF_PLANTING" 0 ((16210.40724 6711.91527) (16248.11652 6694.11810) (16259.42873 6693.06210)))
("SF_PLANTING" 0 ((16210.40724 6711.91527) (16214.17986 6764.70588)))
("SF_MASONRY_AND_ARCH" 0 ((16210.40724 2024.88688) (16229.25905 2032.42172) (16383.86312 2032.43484) (16406.48756
2036.19910) (16432.87896 2032.72477) (16455.50339 2037.25543) (16466.81561 2043.74084)))
("SF_MASONRY_AND_ARCH" 0 ((16210.40724 1734.53903) (16210.40724 1726.99943)))
("SF_MASONRY_AND_ARCH" 0 ((16210.40724 1542.23133) (16251.88348 1542.08428) (16266.96833 1538.46776) (16421.56674
1538.46776) (16436.65158 1542.08428) (16508.28914 1542.37975) (16515.83710 1546.00396)))
("SF_PLANTING" 0 ((16214.17986 6764.70588) (16240.57127 6768.32851) (16270.74095 6761.08326) (16300.90498 6760.93541)))
("SF_PLANTING" 0 ((16225.49208 6613.87658) (16214.17986 6591.25215)))
("SF_MASONRY_AND_ARCH" 0 ((16214.17986 2398.19005) (16300.90498 2395.62364) (16315.98982 2401.81210) (16357.46606
2405.43552) (16368.77828 2402.10826) (16414.02715 2405.43552) (16429.11199 2401.97364) (16485.67308 2405.73179)))
("SF_MASONRY_AND_ARCH" 0 ((16214.17986 2168.17523) (16220.52364 2172.10034) (16221.71946 2183.25792)))
("SF_MASONRY_AND_ARCH" 0 ((16214.17986 1670.43744) (16214.17986 1644.04129)))
("SF_MASONRY_AND_ARCH" 0 ((16481.90045 1738.31165) (16470.58824 1741.93371) (16402.71493 1742.08145) (16346.16075
1738.15633) (16335.89796 1726.99943) (16337.40871 1689.29016) (16330.92262 1679.18281) (16274.50792 1674.36278)
(16229.25905 1677.83020) (16214.17986 1670.43744)))
("SF_MASONRY_AND_ARCH" 0 ((16278.28054 3099.54751) (16266.96833 3103.02183) (16217.94683 3099.54751)))
("SF_MASONRY_AND_ARCH" 0 ((16217.94683 2088.98971) (16217.94683 2070.13575)))
("SF_MASONRY_AND_ARCH" 0 ((16217.94683 2088.98971) (16225.34287 2107.84287) (16221.71946 2122.92636)))
("SF_MASONRY_AND_ARCH" 0 ((16704.37217 2190.79943) (16689.29299 2190.79943) (16538.46154 2190.79943) (16512.06448
2190.79943) (16493.21267 2190.79943) (16368.77828 2190.79943) (16353.69344 2190.79943) (16282.05317 2190.79943)
(16229.26742 2186.88066) (16221.71946 2183.25792)))
("SF_PLANTING" 0 ((16251.88348 6591.25215) (16244.19061 6609.95090) (16225.49208 6613.87658)))
("SF_PLANTING" 0 ((16259.42873 6655.35419) (16240.57127 6655.20633) (16225.65079 6647.66493) (16222.92364 6640.27149)
(16225.49208 6613.87658)))
("SF_PLANTING" 0 ((16233.03167 237.55656) (16225.49208 256.41120)))
("SF_ARCHITECTURE" 0 ((16779.79072 3797.13382) (16764.70588 3793.36391) (16248.11652 3793.37014) (16229.25905
3797.13382)))
("SF_ARCHITECTURE" 0 ((16229.25905 3797.13382) (16229.26742 5693.81606) (16236.80837 5707.69468) (16255.65611
5712.51505) (16274.50984 5701.35747)))
("SF_PLANTING" 0 ((16233.03167 7028.65735) (16248.11652 7021.11640)))
("SF_PLANTING" 0 ((16274.50792 7039.96957) (16280.85317 7047.51787) (16280.99536 7058.82353) (16266.96143 7081.44140)
(16251.88348 7088.82805) (16238.00701 7077.67715) (16233.03167 7028.65735)))
("SF_PLANTING" 0 ((16259.42873 6968.32579) (16233.03167 6968.32579)))
("SF_PLANTING" 0 ((16236.80430 6924.96256) (16229.41516 6938.15667) (16233.03167 6968.32579)))
("SF_PLANTING" 0 ((16236.80430 6990.95023) (16233.03167 6968.32579)))
("SF_PLANTING" 0 ((16353.69344 429.86425) (16338.61425 447.66799) (16289.74050 475.26154) (16237.85928 546.75622)
(16233.03167 565.61086)))
("SF_PLANTING" 0 ((16440.42421 411.00962) (16439.37330 433.63405) (16420.52002 475.11312) (16387.48371 520.36199)
(16353.69344 549.47172) (16312.21719 572.10305) (16233.03167 599.39977) (16214.33314 598.34265) (16210.70962 592.00023)
(16215.37568 576.92930) (16233.03167 565.61086)))
("SF_PLANTING" 0 ((16233.03167 565.61086) (16240.57964 570.75679) (16263.19570 560.78394) (16327.30204 516.44378)
(16375.26290 467.57070) (16387.63009 433.63405)))
("SF_PLANTING" 0 ((16289.59276 252.63857) (16270.74095 237.71120) (16233.03167 237.55656)))
("SF_PLANTING" 0 ((16236.80430 6924.96256) (16248.11652 6912.97217) (16263.19570 6907.99423)))
("SF_PLANTING" 0 ((16236.80430 6924.96256) (16263.19570 6953.24310)))
("SF_MASONRY_AND_ARCH" 0 ((16255.65611 1331.07183) (16240.72738 1329.86697) (16236.80430 1312.21719)))
("SF_PLANTING" 0 ((16300.90498 6772.24762) (16281.90260 6809.95475) (16249.17149 6832.57919) (16240.57127 6862.74536)))
("SF_PLANTING" 0 ((16240.57127 6862.74536) (16259.42873 6866.51584)))
("SF_MASONRY_AND_ARCH" 0 ((16576.17081 1180.24038) (16553.54638 1184.01301) (16406.48756 1180.24729) (16338.61425
1187.62817) (16312.21719 1183.85769) (16297.13235 1176.77296) (16244.34389 1180.24038)))
("SF_MASONRY_AND_ARCH" 0 ((16346.15385 1251.88631) (16338.45814 1236.95679) (16331.06900 1233.18631) (16278.28054
1229.55735) (16259.42873 1232.88394) (16240.72738 1228.95803) (16236.95068 1210.40724) (16244.34389 1180.24038)))
("SF_ARCHITECTURE" 0 ((16315.98982 7971.34242) (16297.13235 7972.54661) (16287.02568 7982.65464) (16280.84762
8024.13281) (16253.08903 8058.06946) (16248.11652 8088.23529)))
("SF_ARCHITECTURE" 0 ((17130.46946 8088.23529) (17149.17353 8093.21041) (17156.71448 8107.08891) (17160.48020
8190.03857) (17153.08552 8197.58676) (16263.19570 8197.58676) (16233.03167 8197.58676) (16218.10294 8197.58676)
(16214.33314 8186.27443) (16214.32624 8110.85973) (16225.49615 8093.21041) (16248.11652 8088.23529)))
("SF_ARCHITECTURE" 0 ((17130.46946 8088.23529) (17111.61199 8092.00611) (16259.42873 8091.99955) (16248.11652
8088.23529)))
("SF_PLANTING" 0 ((16251.88348 6489.44186) (16240.72738 6549.77376) (16251.88348 6591.25215)))
("SF_PLANTING" 0 ((16282.05317 6602.56437) (16263.19570 6592.44966) (16251.88348 6591.25215)))
("SF_PLANTING" 0 ((16711.91742 6489.44186) (16398.94231 6489.43529) (16376.31787 6485.67127) (16266.96833 6485.67783)
(16251.88348 6489.44186)))
("SF_MASONRY_AND_ARCH" 0 ((16278.28054 1421.56957) (16251.88348 1417.79695)))
("SF_PLANTING" 0 ((16259.42873 6968.32579) (16259.42873 6957.01357) (16263.19570 6953.24310)))
("SF_PLANTING" 0 ((16319.75679 7013.57466) (16293.36538 7004.97692) (16271.78767 6987.03145) (16259.42873 6968.32579)))
("SF_PLANTING" 0 ((16259.42873 6866.51584) (16315.98145 6830.00622) (16323.52941 6828.80871)))
("SF_PLANTING" 0 ((16263.19570 6907.99423) (16259.42873 6866.51584)))
("SF_PLANTING" 0 ((16259.42873 6655.35419) (16259.42873 6693.06210)))
("SF_PLANTING" 0 ((16270.74095 6696.83258) (16259.42873 6693.06210)))
("SF_PLANTING" 0 ((16263.19570 6644.04197) (16259.42873 6655.35419)))
("SF_PLANTING" 0 ((16274.50792 6957.01357) (16263.19570 6953.24310)))
("SF_PLANTING" 0 ((16263.19570 6907.99423) (16331.06900 6911.76471)))
("SF_MASONRY_AND_ARCH" 0 ((16346.15385 1877.82805) (16319.75679 1863.94943) (16274.50792 1866.50962) (16263.19570
1862.74536)))
("SF_PLANTING" 0 ((16270.74095 6696.83258) (16270.74095 6715.68654)))
("SF_PLANTING" 0 ((16308.44457 6704.37432) (16308.07726 6693.43020) (16270.74095 6696.83258)))
("SF_ARCHITECTURE" 0 ((16304.67760 5701.35747) (16274.50984 5701.35747)))
("SF_ARCHITECTURE" 0 ((16289.59276 5641.02557) (16274.50984 5652.33812) (16274.50984 5674.96222) (16274.50984
5701.35747)))
("SF_PLANTING" 0 ((16285.82014 6530.91980) (16278.28054 6546.00328)))
("SF_MASONRY_AND_ARCH" 0 ((16874.05543 1327.29921) (16855.20362 1331.06493) (16598.79525 1331.07670) (16579.93778
1334.83541) (16515.83710 1329.40023) (16493.21267 1334.82919) (16474.36086 1331.08428) (16455.50339 1334.83473)
(16357.46606 1331.07183) (16308.44457 1334.84163) (16278.28054 1331.07183)))
("SF_PLANTING" 0 ((16282.05317 6602.56437) (16282.05317 6613.87658)))
("SF_PLANTING" 0 ((16282.05317 6602.56437) (16289.59276 6595.02262)))
("SF_PLANTING" 0 ((16304.67760 343.13631) (16293.51176 347.06222) (16286.87794 358.22115) (16282.05317 395.92760)))
("SF_MASONRY_AND_ARCH" 0 ((16285.82014 3046.75690) (16323.16765 3043.35509) (16330.77489 3069.38133) (16327.30204
3099.54751)))
("SF_MASONRY_AND_ARCH" 0 ((16285.82014 957.76776) (16294.56120 942.83914) (16300.91188 939.06867) (16534.68891
938.90781) (16553.54638 935.14423)))
("SF_MASONRY_AND_ARCH" 0 ((16285.82014 957.76776) (16289.59276 987.93269)))
("SF_ARCHITECTURE" 0 ((16289.59276 5641.02557) (16289.59276 5614.63088)))
("SF_ARCHITECTURE" 0 ((16289.59276 5641.02557) (16308.44649 5656.10860) (16308.44649 5671.19163) (16304.67760
5701.35747)))
("SF_ARCHITECTURE" 0 ((16289.59276 5614.63088) (16308.44649 5603.31799) (16308.44649 5124.43439) (16308.44649
5116.89333) (16289.59276 5101.80995)))
("SF_ARCHITECTURE" 0 ((16289.59276 5614.63088) (16274.50984 5607.08235) (16274.50984 5120.66324) (16274.50984
5113.12217) (16289.59276 5101.80995)))
("SF_ARCHITECTURE" 0 ((16289.59276 5101.80995) (16290.79695 3857.46606) (16308.44649 3838.61278)))
("SF_PLANTING" 0 ((16289.59276 252.63857) (16315.98982 252.63857)))
("SF_MASONRY_AND_ARCH" 0 ((16293.36538 889.89536) (16402.71493 885.97568) (16414.02715 882.35294)))
("SF_MASONRY_AND_ARCH" 0 ((16387.63009 1421.56957) (16297.13235 1421.56957)))
("SF_PLANTING" 0 ((16300.90498 6772.24762) (16300.90498 6760.93541)))
("SF_PLANTING" 0 ((16300.90498 6772.24762) (16334.84163 6779.78857)))
("SF_PLANTING" 0 ((16300.90498 6760.93541) (16304.83088 6749.62975) (16315.98982 6738.31075)))
("SF_ARCHITECTURE" 0 ((16323.52941 7620.66369) (16304.67760 7635.74661)))
("SF_ARCHITECTURE" 0 ((16319.75679 7654.60034) (16304.67760 7635.74661)))
("SF_ARCHITECTURE" 0 ((16357.46606 5701.35747) (16334.84163 5708.89887) (16315.98982 5707.84276) (16304.67760
5701.35747)))
("SF_MASONRY_AND_ARCH" 0 ((16304.67760 3099.54751) (16327.30204 3099.54751)))
("SF_PLANTING" 0 ((16304.67760 343.13631) (16308.29819 331.82410) (16308.44457 294.11765)))
("SF_PLANTING" 0 ((16304.67760 343.13631) (16312.07636 347.06222) (16334.84163 380.84559)))
("SF_PLANTING" 0 ((16308.44457 294.11765) (16312.21719 286.57523) (16315.98982 286.57523)))
("SF_MASONRY_AND_ARCH" 0 ((16312.21719 2500.00000) (16327.30204 2507.54152)))
("SF_ARCHITECTURE" 0 ((17066.36312 7971.34242) (17055.05090 7971.34242) (16410.25452 7971.34242) (16383.86312
7971.34242) (16357.46606 7971.34242) (16315.98982 7971.34242)))
("SF_ARCHITECTURE" 0 ((16315.98982 7835.59581) (16319.75679 7854.44943) (16315.99943 7888.38609) (16319.61041
7903.46912) (16319.75271 7948.71799) (16315.98982 7971.34242)))
("SF_ARCHITECTURE" 0 ((16315.98982 7775.26391) (16319.75679 7790.34695) (16315.98982 7835.59581)))
("SF_ARCHITECTURE" 0 ((16315.98982 7775.26391) (16319.75271 7760.18100) (16319.75679 7654.60034)))
("SF_PLANTING" 0 ((16315.98982 271.49321) (16315.98982 286.57523)))
("SF_PLANTING" 0 ((16315.98982 286.57523) (16338.46369 305.42986) (16353.84955 331.67704) (16372.55090 343.13631)))
("SF_PLANTING" 0 ((16315.98982 271.49321) (16315.98982 252.63857)))
("SF_PLANTING" 0 ((16383.86312 312.97229) (16349.92647 280.09129) (16331.06900 272.54265) (16315.98982 271.49321)))
("SF_PLANTING" 0 ((16436.65158 237.55656) (16421.56674 233.79163) (16338.61425 233.93450) (16323.53631 241.47477)
(16315.98982 252.63857)))
("SF_ARCHITECTURE" 0 ((16319.75679 7654.60034) (16342.38122 7654.60034) (16395.17534 7654.60034) (16990.95023
7654.60034) (17043.73869 7654.60034) (17062.59615 7654.60034)))
("SF_PLANTING" 0 ((16327.30204 6990.95023) (16319.75679 7013.57466)))
("SF_PLANTING" 0 ((16323.52941 7039.96957) (16319.75679 7013.57466)))
("SF_ARCHITECTURE" 0 ((16323.52941 7620.66369) (16512.06448 7620.66369) (16534.68891 7620.66369) (16579.93778
7620.66369) (16595.02262 7620.66369) (16662.89593 7620.66369) (16681.74774 7620.66369) (16768.47851 7620.66369)
(16787.33032 7620.66369) (17043.73869 7620.65713) (17062.59423 7616.89287)))
("SF_ARCHITECTURE" 0 ((16323.52941 7620.66369) (16323.52941 7039.96957)))
("SF_PLANTING" 0 ((16323.52941 7039.96957) (16338.61425 7041.02602) (16353.69344 7048.56731) (16391.40271 7085.21844)))
("SF_PLANTING" 0 ((16334.84163 6779.78857) (16327.44842 6798.64253) (16323.52941 6828.80871)))
("SF_PLANTING" 0 ((16323.52941 6828.80871) (16380.09050 6847.66188)))
("SF_PLANTING" 0 ((16334.84163 6923.07692) (16323.68269 6930.62523) (16319.91290 6938.15962) (16327.30204 6990.95023)))
("SF_PLANTING" 0 ((16327.30204 6990.95023) (16353.69344 6995.77093) (16391.40271 7020.05995) (16406.48756 7024.88688)))
("SF_MASONRY_AND_ARCH" 0 ((16331.06900 3374.81120) (16327.30204 3408.74785)))
("SF_MASONRY_AND_ARCH" 0 ((16327.30204 3408.74785) (16334.84853 3414.04219) (16406.48756 3412.52534) (16417.79977
3416.28959)))
("SF_MASONRY_AND_ARCH" 0 ((16327.30204 3193.81572) (16327.30204 3212.66968)))
("SF_MASONRY_AND_ARCH" 0 ((16327.30204 3193.81572) (16349.92647 3180.07873) (16395.17534 3186.27477)))
("SF_MASONRY_AND_ARCH" 0 ((16417.79977 3103.31799) (16402.71493 3099.55373) (16334.84853 3103.17025) (16327.30204
3099.54751)))
("SF_MASONRY_AND_ARCH" 0 ((16327.30204 2714.93213) (16323.52941 2718.70260) (16327.30204 2722.47387)))
("SF_MASONRY_AND_ARCH" 0 ((16327.30204 2507.54152) (16414.02025 2507.54152) (16421.56674 2507.54152)))
("SF_MASONRY_AND_ARCH" 0 ((16327.30204 2507.54152) (16319.90600 2549.01934) (16319.91290 2590.49774) (16332.12681
2616.73801) (16349.92647 2624.28665) (16410.25452 2628.20486)))
("SF_MASONRY_AND_ARCH" 0 ((16346.15385 1877.82805) (16344.94966 1892.75611) (16327.30204 1896.68201)))
("SF_MASONRY_AND_ARCH" 0 ((16327.30204 1817.49717) (16331.06900 1813.72455) (16338.61425 1817.49717)))
("SF_PLANTING" 0 ((16327.30204 723.98190) (16346.15385 723.98190)))
("SF_PLANTING" 0 ((16346.15385 6900.45249) (16338.75226 6901.65679) (16331.06900 6911.76471)))
("SF_PLANTING" 0 ((16334.84163 6923.07692) (16331.06900 6911.76471)))
("SF_ARCHITECTURE" 0 ((17039.97172 8031.67421) (17017.34729 8035.44502) (16444.19118 8031.67421) (16425.33937
8031.67421) (16334.84163 8031.67421)))
("SF_PLANTING" 0 ((16334.84163 6923.07692) (16368.77828 6956.64502) (16380.09050 6957.01357)))
("SF_PLANTING" 0 ((16334.84163 6779.78857) (16383.86312 6783.55328) (16708.14480 6783.55984)))
("SF_MASONRY_AND_ARCH" 0 ((16338.61425 3344.64581) (16349.92647 3333.48824) (16410.25045 3333.48133) (16417.79977
3337.10407)))
("SF_MASONRY_AND_ARCH" 0 ((16414.02715 2828.05430) (16342.38122 2828.05430)))
("SF_MASONRY_AND_ARCH" 0 ((16342.38122 2760.18100) (16338.76063 2820.50633) (16342.38122 2828.05430)))
("SF_MASONRY_AND_ARCH" 0 ((16342.38122 2828.05430) (16342.53043 2880.84491) (16346.15385 2895.92760)))
("SF_MASONRY_AND_ARCH" 0 ((16342.38122 2760.18100) (16410.25045 2760.03326) (16417.79977 2756.41052)))
("SF_PLANTING" 0 ((16353.69344 429.86425) (16342.38122 407.23982)))
("SF_PLANTING" 0 ((16346.15385 6900.45249) (16368.63054 6877.82805) (16380.09050 6858.97410)))
("SF_PLANTING" 0 ((16455.50339 6930.61867) (16417.79977 6930.47036) (16368.77828 6918.24966) (16346.15385 6900.45249)))
("SF_MASONRY_AND_ARCH" 0 ((16361.23869 3137.25464) (16353.69344 3138.45882) (16346.15385 3148.56686)))
("SF_MASONRY_AND_ARCH" 0 ((16414.02715 2895.92760) (16346.15385 2895.92760)))
("SF_MASONRY_AND_ARCH" 0 ((16346.15385 1877.82805) (16376.31787 1862.90000) (16451.73643 1862.75158) (16478.12783
1866.51584) (16538.46154 1862.74536)))
("SF_MASONRY_AND_ARCH" 0 ((16349.92647 1074.66063) (16365.00566 1078.43043) (16504.52489 1078.42557) (16519.60973
1074.80837) (16564.85860 1074.66753) (16583.71041 1082.20215)))
("SF_PLANTING" 0 ((16349.92647 618.40215) (16383.86312 614.62952)))
("SF_PLANTING" 0 ((16353.69344 429.86425) (16372.55090 429.86425)))
("SF_ARCHITECTURE" 0 ((16357.46606 5701.35747) (16376.31787 5701.35747)))
("SF_ARCHITECTURE" 0 ((16357.46606 5701.35747) (16349.92455 5690.04525) (16349.92455 5674.96222) (16365.00566
5652.33778)))
("SF_MASONRY_AND_ARCH" 0 ((16595.02262 1957.01357) (16500.75226 1957.00735) (16485.67308 1953.39774) (16466.81561
1957.00735) (16440.42421 1953.24932) (16395.17534 1955.81561) (16357.46606 1949.47183)))
("SF_ARCHITECTURE" 0 ((16365.00566 5652.33778) (16365.00566 3849.92500)))
("SF_ARCHITECTURE" 0 ((16376.31787 5701.35747) (16376.16459 5667.42081) (16365.00566 5652.33778)))
("SF_MASONRY_AND_ARCH" 0 ((16365.00566 2598.03948) (16417.79977 2598.03948)))
("SF_MASONRY_AND_ARCH" 0 ((16417.79977 3027.90373) (16406.48756 3031.52647) (16368.77828 3031.67421)))
("SF_PLANTING" 0 ((16372.55090 429.86425) (16373.60588 411.00962) (16399.09287 373.30317) (16410.25452 363.04729)
(16449.84729 346.90894)))
("SF_PLANTING" 0 ((16372.55090 429.86425) (16376.31787 433.63405) (16387.63009 433.63405)))
("SF_PLANTING" 0 ((16372.55090 350.67873) (16372.55090 343.13631)))
("SF_PLANTING" 0 ((16383.86312 312.97229) (16382.66312 328.05430) (16372.55090 343.13631)))
("SF_ARCHITECTURE" 0 ((16376.31787 5701.35747) (16387.63009 5708.74412) (16414.02715 5708.74412) (16432.87896
5693.81606)))
("SF_PLANTING" 0 ((16380.09050 6847.66188) (16380.09050 6858.97410)))
("SF_PLANTING" 0 ((16440.42421 6881.59853) (16406.48756 6876.77206) (16380.09050 6858.97410)))
("SF_PLANTING" 0 ((16455.50339 6847.66188) (16447.95690 6837.40611) (16429.11199 6832.57919) (16406.48756 6833.63518)
(16380.09050 6847.66188)))
("SF_MASONRY_AND_ARCH" 0 ((16383.86312 1685.52036) (16425.33937 1681.75057) (16538.46154 1681.75543) (16561.08597
1685.52036) (16644.04412 1681.75543) (16655.35633 1685.52036)))
("SF_PLANTING" 0 ((16387.63009 818.24943) (16383.86312 825.79186)))
("SF_PLANTING" 0 ((16383.86312 312.97229) (16406.48756 301.66007)))
("SF_PLANTING" 0 ((16387.63009 6738.31075) (16410.25452 6738.31075) (16598.79525 6738.31075) (16617.64706 6738.31075)
(16659.12330 6738.31075)))
("SF_MASONRY_AND_ARCH" 0 ((16387.63009 1421.56957) (16387.63009 1455.50622)))
("SF_MASONRY_AND_ARCH" 0 ((16387.63009 1421.56957) (16402.71493 1402.71493)))
("SF_MASONRY_AND_ARCH" 0 ((16387.63009 1365.00848) (16402.71493 1402.71493)))
("SF_PLANTING" 0 ((16538.46154 554.29864) (16534.54253 584.46550) (16526.09989 610.85973) (16498.04027 671.19061)
(16484.47998 712.66968) (16461.99774 754.14876) (16414.02715 810.56143) (16402.71493 817.19378) (16387.63009
818.24943)))
("SF_PLANTING" 0 ((16387.63009 818.24943) (16387.77930 795.62500) (16402.56719 750.37613) (16403.76437 723.98190)
(16416.60667 697.58767) (16437.70792 625.94174) (16452.77896 599.70215) (16459.27602 595.77771)))
("SF_PLANTING" 0 ((16440.42421 411.00962) (16410.25452 419.75000) (16395.17941 432.43066) (16387.63009 433.63405)))
("SF_MASONRY_AND_ARCH" 0 ((16417.79977 2552.79061) (16391.40271 2556.56109)))
("SF_MASONRY_AND_ARCH" 0 ((16402.71493 1402.71493) (16470.58824 1402.86267) (16489.44005 1406.48473) (16583.71041
1402.86957) (16591.10362 1406.64005) (16602.56222 1425.33937)))
("SF_PLANTING" 0 ((16406.48756 7024.88688) (16421.41346 7006.03292) (16419.00939 6979.79287) (16462.89808 6963.49887)
(16473.16086 6949.47217) (16474.36086 6938.15962)))
("SF_PLANTING" 0 ((16406.48756 7024.88688) (16407.54253 7036.19910) (16417.80385 7051.27523) (16451.73643 7070.13575)))
("SF_MASONRY_AND_ARCH" 0 ((16414.02715 3148.56686) (16410.25452 3141.02590) (16417.79977 3137.25464)))
("SF_PLANTING" 0 ((16436.65158 237.55656) (16431.68314 260.02636) (16414.02715 267.72342)))
("SF_ARCHITECTURE" 0 ((16436.65158 3849.92500) (16436.50385 3925.33937) (16432.88733 3940.42274) (16432.88733
4347.66256) (16436.65158 4370.28699) (16432.88733 4415.53586) (16432.88733 5252.63993) (16436.64468 5271.49321)
(16436.65158 5561.83971) (16432.88733 5584.46414) (16432.87896 5693.81606)))
("SF_ARCHITECTURE" 0 ((16500.75226 5697.58665) (16485.67308 5707.84242) (16459.27602 5708.75068) (16432.87896
5693.81606)))
("SF_PLANTING" 0 ((16436.65158 237.55656) (16474.36086 233.94005) (16485.67308 241.32636)))
("SF_PLANTING" 0 ((16455.50339 6847.66188) (16440.42421 6881.59853)))
("SF_PLANTING" 0 ((16455.50339 6900.45249) (16445.24898 6892.76324) (16440.42421 6881.59853)))
("SF_MASONRY_AND_ARCH" 0 ((16523.37670 2247.36075) (16508.29751 2261.09084) (16451.74050 2258.82760) (16440.42421
2269.98518)))
("SF_MASONRY_AND_ARCH" 0 ((16474.36086 2281.29740) (16455.50339 2283.86369) (16440.42421 2269.98518)))
("SF_PLANTING" 0 ((16444.19118 399.69740) (16440.42421 411.00962)))
("SF_MASONRY_AND_ARCH" 0 ((16444.19118 2100.30192) (16451.74050 2103.91776) (16463.04864 2100.30192)))
("SF_MASONRY_AND_ARCH" 0 ((16451.73643 995.47511) (16444.19118 987.93269)))
("SF_PLANTING" 0 ((16444.19118 399.69740) (16466.81561 398.64174) (16477.98145 392.00939) (16485.67308 380.84559)))
("SF_PLANTING" 0 ((16444.19118 399.69740) (16451.58722 361.99095) (16449.84729 346.90894)))
("SF_PLANTING" 0 ((16449.84729 346.90894) (16463.04310 345.85181) (16481.75271 335.44830) (16509.35249 275.26301)
(16530.92195 252.63857)))
("SF_PLANTING" 0 ((16485.67308 241.32636) (16480.99186 260.18100) (16452.93224 305.42986) (16448.11154 328.05430)
(16449.84729 346.90894)))
("SF_MASONRY_AND_ARCH" 0 ((16451.73643 995.47511) (16449.16799 1018.09265) (16470.21957 1029.62647) (16470.58824
1036.95419)))
("SF_MASONRY_AND_ARCH" 0 ((16451.73643 995.47511) (16474.36086 999.09785) (16538.46154 992.00079) (16572.39819
999.24491) (16621.41968 995.48133) (16745.85407 995.47511)))
("SF_MASONRY_AND_ARCH" 0 ((16542.23416 889.89536) (16459.28292 889.74695) (16451.73643 886.12274)))
("SF_PLANTING" 0 ((16455.50339 6930.61867) (16455.50339 6900.45249)))
("SF_PLANTING" 0 ((16455.50339 6930.61867) (16474.36086 6938.15962)))
("SF_PLANTING" 0 ((16478.12783 6847.66188) (16492.15633 6870.28631) (16492.00848 6881.59853) (16478.12783 6893.80611)
(16455.50339 6900.45249)))
("SF_PLANTING" 0 ((16478.12783 6847.66188) (16455.50339 6847.66188)))
("SF_MASONRY_AND_ARCH" 0 ((16666.66855 2322.77500) (16553.54638 2322.78122) (16538.46154 2326.25000) (16523.37670
2320.20871) (16470.58824 2322.76878) (16459.27602 2319.00452)))
("SF_PLANTING" 0 ((16459.27602 595.77771) (16459.42376 561.84106) (16494.26900 478.88292) (16508.29751 467.57070)))
("SF_PLANTING" 0 ((16489.44005 618.40215) (16459.27602 595.77771)))
("SF_MASONRY_AND_ARCH" 0 ((16463.04864 2100.30192) (16466.81561 2043.74084)))
("SF_MASONRY_AND_ARCH" 0 ((16523.37670 2100.30192) (16504.52489 2104.07240) (16470.59514 2103.92466) (16463.04864
2100.30192)))
("SF_MASONRY_AND_ARCH" 0 ((16478.12783 2039.96957) (16466.81561 2043.74084)))
("SF_PLANTING" 0 ((16546.00113 6900.45249) (16519.60973 6912.81414) (16496.98529 6929.56222) (16474.36086 6938.15962)))
("SF_PLANTING" 0 ((16478.12783 6847.66188) (16489.44005 6840.27534) (16527.14242 6840.26878) (16534.68891 6843.89140)))
("SF_PLANTING" 0 ((16481.90045 825.79186) (16553.54638 825.64412) (16572.39819 822.02206) (16606.33484 825.79186)))
("SF_MASONRY_AND_ARCH" 0 ((16485.67308 2590.49774) (16523.37670 2574.21086) (16538.46154 2556.56109)))
("SF_MASONRY_AND_ARCH" 0 ((16485.67308 2590.49774) (16474.35894 2579.18552) (16478.28394 2556.56799) (16482.05373
2550.22353) (16527.14932 2549.17398) (16538.46154 2556.56109)))
("SF_MASONRY_AND_ARCH" 0 ((16489.44005 3340.87455) (16489.43597 3254.14808) (16485.67715 3235.29412) (16485.81946
3193.81572) (16489.43597 3178.73303) (16489.29367 3137.25464) (16485.67715 3122.17195) (16485.67308 2854.44921)
(16489.29367 2835.59604) (16489.44005 2760.18100) (16485.67715 2737.55656) (16485.67308 2590.49774)))
("SF_PLANTING" 0 ((16485.67308 241.32636) (16515.83710 241.48167) (16530.92195 252.63857)))
("SF_MASONRY_AND_ARCH" 0 ((16527.14932 3374.81120) (16508.29751 3385.97500) (16489.44005 3385.96878) (16482.05373
3382.19830) (16474.35894 3374.81120) (16474.35894 3352.18676) (16489.44005 3340.87455)))
("SF_MASONRY_AND_ARCH" 0 ((16527.14932 3374.81120) (16511.91810 3356.10577) (16489.44005 3340.87455)))
("SF_PLANTING" 0 ((16496.98529 550.52885) (16496.98529 561.84106)))
("SF_ARCHITECTURE" 0 ((16500.75226 5697.58665) (16504.52489 5629.71335) (16504.51799 5094.26889) (16500.75226
5071.64446) (16500.76063 4479.63801) (16504.52489 4457.01357) (16504.37715 4374.05690) (16500.76063 4358.97477)
(16500.76063 3978.12930) (16504.51799 3959.27602) (16504.51799 3861.23722) (16500.75226 3849.92500)))
("SF_ARCHITECTURE" 0 ((16500.75226 5697.58665) (16519.60973 5708.74412) (16549.77376 5705.12828)))
("SF_MASONRY_AND_ARCH" 0 ((16500.75226 1606.33484) (16515.83710 1598.79242)))
("SF_MASONRY_AND_ARCH" 0 ((16504.52489 3533.18224) (16512.06448 3536.95351)))
("SF_MASONRY_AND_ARCH" 0 ((16515.83710 1466.81844) (16508.29751 1463.04581)))
("SF_MASONRY_AND_ARCH" 0 ((16508.29751 1274.51075) (16508.29751 1255.65611)))
("SF_MASONRY_AND_ARCH" 0 ((16515.83710 1285.82296) (16508.29751 1274.51075)))
("SF_PLANTING" 0 ((16553.54638 312.97229) (16538.61482 320.66029) (16527.29706 354.44853) (16527.00158 384.61538)
(16508.29751 467.57070)))
("SF_PLANTING" 0 ((16538.46154 554.29864) (16528.34514 542.98643) (16519.45362 482.65554) (16508.29751 467.57070)))
("SF_MASONRY_AND_ARCH" 0 ((16512.06448 2405.73179) (16527.14932 2406.78812) (16538.30826 2413.42127) (16546.00113
2435.89717)))
("SF_MASONRY_AND_ARCH" 0 ((16583.71041 2036.19910) (16512.06448 2036.19910)))
("SF_MASONRY_AND_ARCH" 0 ((16519.60973 1233.03167) (16512.06448 1233.03167)))
("SF_MASONRY_AND_ARCH" 0 ((16538.46154 1598.79242) (16515.83710 1598.79242)))
("SF_MASONRY_AND_ARCH" 0 ((16515.83710 1598.79242) (16512.36143 1564.85577) (16515.83710 1546.00396)))
("SF_MASONRY_AND_ARCH" 0 ((16866.51584 1549.77376) (16825.03959 1553.24808) (16791.10294 1549.92149) (16772.24548
1553.53733) (16753.39367 1549.77998) (16515.83710 1546.00396)))
("SF_MASONRY_AND_ARCH" 0 ((16681.74774 1459.27602) (16606.33484 1459.42376) (16587.48303 1463.04581) (16530.92195
1459.42443) (16515.83710 1466.81844)))
("SF_MASONRY_AND_ARCH" 0 ((16515.83710 1466.81844) (16515.98484 1493.20577) (16519.60973 1500.75509)))
("SF_MASONRY_AND_ARCH" 0 ((16523.37670 2247.36075) (16519.60973 2243.58948) (16519.60973 2232.27726)))
("SF_MASONRY_AND_ARCH" 0 ((16523.37670 2247.36075) (16542.23416 2251.13122) (16644.04412 2251.12500) (16659.12330
2247.51538) (16677.98077 2250.97658) (16696.83258 2247.36075)))
("SF_MASONRY_AND_ARCH" 0 ((16523.37670 1742.08145) (16530.92602 1745.69796) (16549.77376 1742.08145)))
("SF_PLANTING" 0 ((16564.85860 6972.09627) (16538.46844 6978.42715) (16527.14932 6960.78405)))
("SF_MASONRY_AND_ARCH" 0 ((16527.14932 3374.81120) (16549.77376 3374.81120)))
("SF_PLANTING" 0 ((16564.85860 267.72342) (16553.39581 253.84344) (16530.92195 252.63857)))
("SF_PLANTING" 0 ((16561.08597 6840.12093) (16534.68891 6843.89140)))
("SF_PLANTING" 0 ((16551.65724 6887.25464) (16542.44955 6881.51810) (16535.74672 6870.28631) (16534.68891 6843.89140)))
("SF_MASONRY_AND_ARCH" 0 ((16546.00113 2556.56109) (16538.46154 2556.56109)))
("SF_MASONRY_AND_ARCH" 0 ((16538.46154 1862.74536) (16538.60928 1817.50204) (16542.23416 1809.95475)))
("SF_MASONRY_AND_ARCH" 0 ((16538.46154 1862.74536) (16613.87443 1862.89310) (16632.73190 1866.51584)))
("SF_MASONRY_AND_ARCH" 0 ((16538.46154 1779.78790) (16538.60928 1802.40747) (16542.23416 1809.95475)))
("SF_PLANTING" 0 ((16564.85860 554.29864) (16538.46154 554.29864)))
("SF_ARCHITECTURE" 0 ((16542.23224 5049.02002) (16542.23224 4966.06335)))
("SF_ARCHITECTURE" 0 ((16542.23224 4890.64898) (16542.23224 4494.72138)))
("SF_MASONRY_AND_ARCH" 0 ((16542.23416 2458.52161) (16546.00113 2435.89717)))
("SF_MASONRY_AND_ARCH" 0 ((16719.45701 1862.74536) (16719.30373 1825.03744) (16708.14480 1811.15962) (16542.23416
1809.95475)))
("SF_PLANTING" 0 ((16551.65724 6887.25464) (16546.00113 6892.91075) (16546.00113 6900.45249)))
("SF_PLANTING" 0 ((16546.00113 6900.45249) (16556.11063 6911.76471) (16558.51199 6926.84084) (16564.85860 6934.38914)))
("SF_ARCHITECTURE" 0 ((16546.00113 5584.46414) (16543.42998 5592.01267) (16549.77376 5705.12828)))
("SF_MASONRY_AND_ARCH" 0 ((16546.00113 2556.56109) (16557.31335 2549.17398) (16583.71041 2549.17398) (16591.09672
2552.94525) (16594.86934 2560.33156) (16594.86934 2582.95600) (16583.71041 2594.26821)))
("SF_MASONRY_AND_ARCH" 0 ((16546.00113 2556.56109) (16568.62557 2582.95600) (16583.71041 2594.26821)))
("SF_MASONRY_AND_ARCH" 0 ((16546.00113 2435.89717) (16576.17081 2435.74943) (16610.10747 2428.50396) (16666.66018
2428.20848) (16674.20814 2424.58495)))
("SF_ARCHITECTURE" 0 ((16579.93778 5701.35747) (16572.39129 5704.98020) (16549.77376 5705.12828)))
("SF_MASONRY_AND_ARCH" 0 ((16549.77376 3374.81120) (16561.23371 3356.10577) (16583.71041 3337.10407)))
("SF_MASONRY_AND_ARCH" 0 ((16549.77376 3374.81120) (16564.85860 3385.96878) (16583.71041 3385.96878) (16594.86934
3378.57557) (16598.63914 3355.95803) (16583.71041 3337.10407)))
("SF_MASONRY_AND_ARCH" 0 ((16553.54638 935.14423) (16549.77376 920.05939)))
("SF_PLANTING" 0 ((16561.08597 6840.12093) (16560.92851 6874.06052) (16551.65724 6887.25464)))
("SF_PLANTING" 0 ((16551.65724 6887.25464) (16579.93778 6893.96753) (16606.33484 6910.57353) (16651.58371 6923.07692)))
("SF_ARCHITECTURE" 0 ((16553.54638 4321.26697) (16549.77376 4287.33032) (16553.54638 4253.39367) (16549.78066
4226.99808) (16553.54638 4200.60373) (16549.78066 4128.95928) (16553.54638 4117.64706)))
("SF_MASONRY_AND_ARCH" 0 ((16553.54638 935.14423) (16602.56222 938.91403)))
("SF_PLANTING" 0 ((16553.54638 312.97229) (16553.69966 282.80543) (16564.85860 267.72342)))
("SF_PLANTING" 0 ((16553.54638 312.97229) (16563.65305 324.28450) (16568.77477 373.30317) (16587.48303 429.86425)))
("SF_MASONRY_AND_ARCH" 0 ((16655.35633 1602.56505) (16640.27149 1598.94084) (16595.02262 1602.55747) (16557.31335
1598.79242)))
("SF_PLANTING" 0 ((16561.08597 6840.12093) (16610.09910 6840.26878) (16617.64706 6843.89140)))
("SF_MASONRY_AND_ARCH" 0 ((16568.62557 1285.82296) (16561.08597 1285.82296)))
("SF_PLANTING" 0 ((16564.85860 6972.09627) (16564.85860 6934.38914)))
("SF_PLANTING" 0 ((16564.85860 6972.09627) (16579.93371 6973.30057) (16595.02952 6989.75249) (16613.87443 6994.56629)
(16627.90294 6987.03145) (16632.73190 6964.55532)))
("SF_PLANTING" 0 ((16583.71041 6930.61867) (16564.85860 6934.38914)))
("SF_MASONRY_AND_ARCH" 0 ((16595.02262 2107.84287) (16576.17081 2111.45950) (16564.85860 2107.84287)))
("SF_PLANTING" 0 ((16591.25000 493.96776) (16569.82557 512.82715) (16565.00498 527.90441) (16564.85860 554.29864)))
("SF_PLANTING" 0 ((16564.85860 554.29864) (16596.07896 674.96324) (16622.46640 735.29412) (16656.54525 795.62500)
(16681.89830 829.56165) (16704.37217 851.13043) (16723.07353 857.47489) (16726.84333 852.17364) (16726.85023 833.33428)
(16719.60475 806.93722) (16719.30928 788.08541) (16685.66810 674.96324) (16678.12715 637.25396) (16677.98077
614.62952)))
("SF_PLANTING" 0 ((16564.85860 267.72342) (16572.39819 267.72342)))
("SF_PLANTING" 0 ((16628.95928 241.32636) (16595.02262 242.53122) (16572.39819 267.72342)))
("SF_PLANTING" 0 ((16617.64706 312.97229) (16605.27851 290.50113) (16587.48303 281.74910) (16572.39819 267.72342)))
("SF_ARCHITECTURE" 0 ((16576.17081 3838.61278) (16579.93371 3849.92500) (16579.93778 5701.35747)))
("SF_MASONRY_AND_ARCH" 0 ((16576.17081 1180.24038) (16576.17081 1168.92817)))
("SF_MASONRY_AND_ARCH" 0 ((16576.17081 1180.24038) (16632.73190 1180.38880) (16651.58371 1184.01301) (16693.05995
1180.24038)))
("SF_ARCHITECTURE" 0 ((16579.93778 5701.35747) (16602.56222 5708.89887) (16625.18857 5707.70124) (16625.18857
5701.35747)))
("SF_MASONRY_AND_ARCH" 0 ((16636.49887 3514.32907) (16579.93778 3503.01686)))
("SF_MASONRY_AND_ARCH" 0 ((17179.48529 1745.85124) (17160.63348 1742.08145) (17119.15724 1745.84638) (17028.65950
1745.70419) (16990.95023 1738.31652) (16870.28846 1738.31652) (16847.66403 1742.08145) (16787.33032 1738.31165)
(16753.39367 1741.92681) (16734.54186 1738.31787) (16715.68439 1742.06900) (16651.58371 1736.64005) (16587.48710
1738.45871) (16579.93778 1742.08145)))
("SF_MASONRY_AND_ARCH" 0 ((16579.93778 1119.90950) (16587.48710 1127.29661) (16659.12330 1123.67930)))
("SF_MASONRY_AND_ARCH" 0 ((16583.71041 1082.20215) (16579.93778 1093.51527)))
("SF_MASONRY_AND_ARCH" 0 ((16583.71041 3322.02138) (16583.71041 3337.10407)))
("SF_MASONRY_AND_ARCH" 0 ((16583.71041 3227.75238) (16597.58971 3242.83586) (16598.63914 3306.93790) (16594.86934
3314.47274) (16583.71041 3322.02138)))
("SF_MASONRY_AND_ARCH" 0 ((16583.71041 3227.75238) (16568.62749 3239.06459) (16568.62749 3310.70916) (16583.71041
3322.02138)))
("SF_MASONRY_AND_ARCH" 0 ((16583.71041 3227.75238) (16583.71041 2594.26821)))
("SF_MASONRY_AND_ARCH" 0 ((16583.71041 1082.20215) (16670.43552 1082.20215) (16689.29299 1082.20215) (16757.16629
1082.20215) (16776.01810 1082.20215) (16821.26697 1082.20215) (16840.11878 1082.20215) (17039.97172 1082.20215)
(17073.90837 1082.20215)))
("SF_PLANTING" 0 ((16587.48303 429.86425) (16640.27149 418.55204)))
("SF_PLANTING" 0 ((16591.25000 493.96776) (16587.48303 429.86425)))
("SF_PLANTING" 0 ((16591.25000 493.96776) (16628.95928 506.33563) (16647.95475 531.51957) (16655.35633 535.44400)))
("SF_MASONRY_AND_ARCH" 0 ((16602.56222 920.05939) (16602.56222 938.91403)))
("SF_MASONRY_AND_ARCH" 0 ((16889.14027 957.76867) (16809.95475 950.23247) (16666.66855 950.07851) (16621.41968
946.30803) (16602.56222 938.91403)))
("SF_MASONRY_AND_ARCH" 0 ((16602.56222 889.89536) (16610.10747 882.35294)))
("SF_PLANTING" 0 ((16610.10747 554.29864) (16602.56222 546.75622)))
("SF_PLANTING" 0 ((16613.87443 569.38066) (16610.10747 580.69287)))
("SF_PLANTING" 0 ((16632.73190 6964.55532) (16613.87443 6953.24310)))
("SF_MASONRY_AND_ARCH" 0 ((16613.87443 2032.42862) (16644.04412 2039.96957)))
("SF_PLANTING" 0 ((16617.64706 6843.89140) (16651.58371 6843.89140)))
("SF_PLANTING" 0 ((16617.64706 6843.89140) (16622.61550 6866.51584) (16632.73190 6877.67319) (16655.34796 6885.07353)
(16662.89593 6881.59853)))
("SF_PLANTING" 0 ((16625.18665 316.74208) (16617.64706 320.51188)))
("SF_PLANTING" 0 ((16617.64706 312.97229) (16617.64706 320.51188)))
("SF_PLANTING" 0 ((16649.70023 401.58371) (16618.69649 350.67873) (16613.88824 331.82410) (16617.64706 320.51188)))
("SF_PLANTING" 0 ((16625.18665 316.74208) (16617.64706 312.97229)))
("SF_MASONRY_AND_ARCH" 0 ((16651.58371 2104.07240) (16621.41968 2107.84287)))
("SF_PLANTING" 0 ((16625.18665 316.74208) (16632.73597 317.94695) (16655.35633 339.21188) (16666.66855 343.13631)))
("SF_ARCHITECTURE" 0 ((16655.35441 5701.35747) (16625.18857 5701.35747)))
("SF_ARCHITECTURE" 0 ((16632.73190 5158.37104) (16625.18857 5169.68326) (16625.18857 5701.35747)))
("SF_ARCHITECTURE" 0 ((16644.04412 3853.69491) (16625.18857 3834.84163)))
("SF_MASONRY_AND_ARCH" 0 ((16628.95928 1285.82296) (16659.12330 1285.82296)))
("SF_PLANTING" 0 ((16636.49887 629.71437) (16628.95928 625.94174)))
("SF_PLANTING" 0 ((16726.99661 245.09898) (16708.14480 233.93450) (16644.04412 233.93450) (16628.95928 241.32636)))
("SF_PLANTING" 0 ((16681.74774 328.05430) (16665.61765 297.88744) (16633.93462 260.18100) (16628.95928 241.32636)))
("SF_PLANTING" 0 ((16632.73190 6964.55532) (16666.66855 6938.32104) (16693.05995 6942.98032) (16715.68439 6953.24310)))
("SF_ARCHITECTURE" 0 ((16632.73190 5158.37104) (16655.35441 5158.37104)))
("SF_ARCHITECTURE" 0 ((16640.27149 5116.89333) (16625.18857 5131.97545) (16632.73190 5158.37104)))
("SF_MASONRY_AND_ARCH" 0 ((16870.28846 1957.01357) (16851.43100 1953.24310) (16806.18213 1957.01357) (16760.93326
1953.24310) (16708.14480 1957.00667) (16689.29299 1953.53925) (16674.20814 1956.85894) (16644.04412 1953.24932)
(16632.73190 1957.01357)))
("SF_MASONRY_AND_ARCH" 0 ((16719.45701 1862.74536) (16647.81109 1862.89310) (16632.73190 1866.51584)))
("SF_MASONRY_AND_ARCH" 0 ((16636.49887 1877.82805) (16632.73190 1866.51584)))
("SF_MASONRY_AND_ARCH" 0 ((16632.73190 1421.56957) (16659.12330 1427.91199) (16768.47851 1425.34559) (16787.33032
1429.10430) (16960.78620 1429.11606) (17009.80204 1432.88179)))
("SF_ARCHITECTURE" 0 ((16640.27149 5082.95667) (16640.27149 5116.89333)))
("SF_ARCHITECTURE" 0 ((16640.27149 5116.89333) (16655.35441 5135.74661) (16655.35441 5158.37104)))
("SF_ARCHITECTURE" 0 ((16640.27149 5082.95667) (16655.35441 5071.64378) (16655.35441 4947.21007) (16655.35441
4917.04400) (16640.27149 4905.73111)))
("SF_ARCHITECTURE" 0 ((16640.27149 5082.95667) (16625.18857 5075.40814) (16625.18857 4920.81448) (16640.27149
4905.73111)))
("SF_ARCHITECTURE" 0 ((16640.27149 4905.73111) (16640.27839 4445.70136) (16644.03575 4426.84808) (16640.27839
4404.22364) (16640.27149 4279.78925)))
("SF_ARCHITECTURE" 0 ((16640.27149 4177.97930) (16655.35441 4189.29152) (16655.35441 4268.47636) (16640.27149
4279.78925)))
("SF_ARCHITECTURE" 0 ((16640.27149 4177.97930) (16625.18857 4189.29152) (16625.18857 4268.47636) (16640.27149
4279.78925)))
("SF_ARCHITECTURE" 0 ((16640.27149 4177.97930) (16640.27149 4166.66708)))
("SF_ARCHITECTURE" 0 ((16644.04412 4091.25147) (16655.35441 4110.10600) (16655.35441 4151.58371) (16655.35441
4159.11855) (16640.27149 4166.66708)))
("SF_ARCHITECTURE" 0 ((16644.04412 4091.25147) (16632.88518 4098.80000) (16625.18857 4106.33484) (16625.18857
4151.58371) (16633.77862 4162.74129) (16640.27149 4166.66708)))
("SF_PLANTING" 0 ((16649.70023 401.58371) (16640.27149 411.00962) (16640.27149 418.55204)))
("SF_PLANTING" 0 ((16685.52036 527.90441) (16676.92296 490.19514) (16652.77952 448.71889) (16640.27149 418.55204)))
("SF_ARCHITECTURE" 0 ((16644.04412 4091.25147) (16643.89491 4015.83710) (16640.27149 3996.98382) (16644.04412
3853.69491)))
("SF_ARCHITECTURE" 0 ((16655.35441 3842.38269) (16644.04412 3853.69491)))
("SF_PLANTING" 0 ((16674.20814 373.30317) (16649.70023 401.58371)))
("SF_PLANTING" 0 ((16715.68439 471.34333) (16700.75158 463.79400) (16674.06041 422.32183) (16649.70023 401.58371)))
("SF_PLANTING" 0 ((16715.68439 6840.12093) (16696.83258 6832.72749) (16677.98077 6832.72749) (16659.13167 6837.54740)
(16651.58371 6843.89140)))
("SF_PLANTING" 0 ((16662.89593 6881.59853) (16651.58371 6843.89140)))
("SF_MASONRY_AND_ARCH" 0 ((16776.01810 3273.00124) (16749.62104 3258.06697) (16651.58371 3254.14808)))
("SF_MASONRY_AND_ARCH" 0 ((16892.91290 2511.31222) (16885.36357 2507.68948) (16783.55769 2507.53552) (16764.70588
2503.77670) (16670.43552 2507.54152) (16651.58371 2507.54152)))
("SF_MASONRY_AND_ARCH" 0 ((16655.35633 1685.52036) (16651.58371 1696.83258)))
("SF_MASONRY_AND_ARCH" 0 ((16651.58371 1640.27149) (16655.35633 1602.56505)))
("SF_ARCHITECTURE" 0 ((16655.35441 5701.35747) (16655.35441 5173.45441) (16655.35441 5158.37104)))
("SF_ARCHITECTURE" 0 ((16696.83258 5705.12828) (16689.28462 5708.75068) (16666.66855 5708.74412) (16655.35441
5701.35747)))
("SF_MASONRY_AND_ARCH" 0 ((16892.91290 3050.52794) (16862.74321 3050.52794) (16843.89140 3050.52794) (16813.72738
3050.52794) (16764.70588 3050.52794) (16742.08145 3050.52794) (16666.66855 3050.52794) (16655.35633 3050.52794)))
("SF_MASONRY_AND_ARCH" 0 ((16677.98077 2779.03495) (16655.35633 2767.72274)))
("SF_MASONRY_AND_ARCH" 0 ((16670.43552 1689.29016) (16666.66855 1685.52036) (16655.35633 1685.52036)))
("SF_MASONRY_AND_ARCH" 0 ((16806.18213 1602.56505) (16779.79072 1598.79242) (16670.43552 1598.79932) (16655.35633
1602.56505)))
("SF_PLANTING" 0 ((16685.52036 527.90441) (16655.35633 535.44400)))
("SF_PLANTING" 0 ((16655.35633 535.44400) (16655.50271 554.29864) (16663.94536 584.46550) (16677.98077 614.62952)))
("SF_PLANTING" 0 ((16715.68439 6953.24310) (16704.22579 6982.35249) (16677.98077 6990.80192) (16659.12330 6990.95023)))
("SF_MASONRY_AND_ARCH" 0 ((16659.12330 3514.32907) (16685.52036 3518.09955) (16760.93326 3517.95181) (16776.01810
3514.34219) (16794.86991 3517.94491) (16813.72738 3514.32907)))
("SF_MASONRY_AND_ARCH" 0 ((16659.12330 3340.87455) (16685.52036 3344.64581)))
("SF_MASONRY_AND_ARCH" 0 ((16693.05995 3103.31799) (16670.43552 3117.34502) (16659.12330 3118.40147)))
("SF_MASONRY_AND_ARCH" 0 ((16659.12330 2895.92760) (16674.20814 2899.69186) (16745.85407 2896.07534) (16776.01810
2903.46312) (16870.28846 2903.46934)))
("SF_PLANTING" 0 ((16662.89593 6881.59853) (16711.91742 6889.14027)))
("SF_MASONRY_AND_ARCH" 0 ((17130.46946 3182.50351) (17111.61199 3186.27477) (16821.26697 3186.26855) (16806.18213
3182.79977) (16734.54186 3197.43925) (16715.68439 3197.43925) (16670.43552 3188.84729) (16659.27941 3174.96256)
(16662.89593 3159.87907)))
("SF_MASONRY_AND_ARCH" 0 ((16666.66855 2609.35170) (16663.26459 2631.75520) (16674.20396 2635.60158) (16742.08145
2639.51708) (16836.35181 2635.75283) (16866.51584 2639.51708)))
("SF_MASONRY_AND_ARCH" 0 ((16666.66855 2322.77500) (16666.66855 2352.94118)))
("SF_MASONRY_AND_ARCH" 0 ((16666.66855 2322.77500) (16677.98077 2316.29038) (16708.14480 2311.46278)))
("SF_PLANTING" 0 ((16681.74774 328.05430) (16666.66855 343.13631)))
("SF_PLANTING" 0 ((16674.20814 373.30317) (16666.66855 343.13631)))
("SF_MASONRY_AND_ARCH" 0 ((16670.43552 2801.65939) (16677.98077 2779.03495)))
("SF_MASONRY_AND_ARCH" 0 ((16670.43552 1123.67930) (16719.45701 1127.45192) (16738.30882 1123.67930)))
("SF_PLANTING" 0 ((16674.20814 7107.84287) (16671.64106 7092.76018) (16685.66810 7074.05475) (16696.83258 7068.47070)
(16723.22964 7068.93801) (16760.93326 7036.19910)))
("SF_MASONRY_AND_ARCH" 0 ((16674.20814 2858.22048) (16670.43552 2843.13699) (16674.20814 2824.28382)))
("SF_MASONRY_AND_ARCH" 0 ((16674.20814 2424.58495) (16674.20814 2413.27274)))
("SF_MASONRY_AND_ARCH" 0 ((16764.70588 2428.35622) (16685.52036 2428.20848) (16674.20814 2424.58495)))
("SF_MASONRY_AND_ARCH" 0 ((16794.86991 2043.74084) (16760.93326 2039.97579) (16674.20814 2039.96957)))
("SF_PLANTING" 0 ((16674.20814 373.30317) (16696.83258 377.07296)))
("SF_MASONRY_AND_ARCH" 0 ((16677.98077 2779.03495) (16813.72738 2779.03473) (16858.96787 2779.03473) (16866.51584
2779.03473)))
("SF_MASONRY_AND_ARCH" 0 ((16685.52036 1285.82296) (16677.98077 1289.59276)))
("SF_PLANTING" 0 ((16693.05995 618.40215) (16689.29299 614.62952) (16677.98077 614.62952)))
("SF_PLANTING" 0 ((16681.74774 328.05430) (16696.83258 323.22738) (16706.94061 312.97229) (16713.11324 282.80543)
(16726.99661 245.09898)))
("SF_MASONRY_AND_ARCH" 0 ((16685.52036 3344.64581) (16760.93326 3337.25181) (16828.80656 3337.10407)))
("SF_MASONRY_AND_ARCH" 0 ((16685.52036 3344.64581) (16689.29299 3371.04072)))
("SF_MASONRY_AND_ARCH" 0 ((16685.52036 2107.84287) (16719.45701 2111.61414)))
("SF_PLANTING" 0 ((16685.52036 527.90441) (16753.40057 603.31731) (16779.79072 624.88676) (16877.82805 673.77217)
(16904.06210 681.15102) (16906.78937 674.95566) (16899.26222 648.56618) (16876.77172 610.85973) (16806.03575 516.59219)
(16749.62104 467.57070)))
("SF_MASONRY_AND_ARCH" 0 ((16693.05995 3469.07998) (16689.29299 3442.68450)))
("SF_MASONRY_AND_ARCH" 0 ((16689.29299 3092.00577) (16693.05995 3103.31799)))
("SF_MASONRY_AND_ARCH" 0 ((16693.05995 3469.07998) (16704.37217 3469.07998) (16764.70588 3469.07998) (16776.01810
3469.07998) (16866.51584 3469.07998)))
("SF_MASONRY_AND_ARCH" 0 ((16768.47851 3107.08925) (16700.60928 3106.94152) (16693.05995 3103.31799)))
("SF_MASONRY_AND_ARCH" 0 ((16693.05995 1165.15837) (16693.05995 1180.24038)))
("SF_MASONRY_AND_ARCH" 0 ((16693.05995 1180.24038) (16704.37217 1183.86459) (16855.20362 1184.01787) (16874.05543
1187.78281)))
("SF_ARCHITECTURE" 0 ((16696.83258 5705.12828) (16730.76923 5705.12828)))
("SF_ARCHITECTURE" 0 ((16696.83258 5705.12828) (16696.83258 4543.74016) (16711.91742 4528.65803)))
("SF_ARCHITECTURE" 0 ((16696.83258 3834.84163) (16700.60520 3842.38269)))
("SF_MASONRY_AND_ARCH" 0 ((16704.37217 2190.79943) (16696.83258 2247.36075)))
("SF_MASONRY_AND_ARCH" 0 ((16708.14480 2311.46278) (16704.21889 2262.44344) (16696.83258 2247.36075)))
("SF_MASONRY_AND_ARCH" 0 ((16696.83258 1244.34389) (16730.76923 1251.73790) (16825.03959 1251.88631)))
("SF_PLANTING" 0 ((16757.16629 312.97229) (16747.04989 324.28450) (16734.39129 354.44853) (16723.22964 364.70509)
(16696.83258 377.07296)))
("SF_PLANTING" 0 ((16753.39367 433.63405) (16715.68439 407.23982) (16701.80792 392.15781) (16696.83258 377.07296)))
("SF_ARCHITECTURE" 0 ((16711.91742 4362.74468) (16696.98586 4381.59921) (16700.60520 4453.24242)))
("SF_ARCHITECTURE" 0 ((16711.91742 4521.11572) (16704.51584 4517.19084) (16696.83258 4502.26244) (16696.98032
4460.79095) (16700.60520 4453.24242)))
("SF_ARCHITECTURE" 0 ((16730.76923 4457.01357) (16700.60520 4453.24242)))
("SF_ARCHITECTURE" 0 ((16700.60520 3842.38269) (16723.22964 3842.38269)))
("SF_ARCHITECTURE" 0 ((16711.91742 4336.35034) (16701.66018 4328.80181) (16696.83948 4313.72590) (16696.83948
4181.74921) (16700.60520 4159.12477) (16700.59683 3932.88043) (16696.98032 3917.79830) (16696.83948 3853.69559)
(16700.60520 3842.38269)))
("SF_MASONRY_AND_ARCH" 0 ((16704.37217 2190.79943) (16711.91742 2183.25792)))
("SF_MASONRY_AND_ARCH" 0 ((16704.37217 1693.06278) (16730.76923 1689.29016)))
("SF_PLANTING" 0 ((16715.68439 6757.16414) (16708.14480 6783.55984)))
("SF_PLANTING" 0 ((16715.68439 6840.12093) (16726.70249 6813.72523) (16722.02964 6798.64253) (16708.14480 6783.55984)))
("SF_MASONRY_AND_ARCH" 0 ((17179.48529 2315.23405) (17160.63348 2318.99830) (17047.51131 2318.99830) (17024.88688
2315.23405) (16904.22511 2315.24027) (16874.05543 2318.99830) (16855.20362 2315.24027) (16715.69276 2315.08631)
(16708.14480 2311.46278)))
("SF_MASONRY_AND_ARCH" 0 ((16711.91742 2183.25792) (16708.14480 2171.94570)))
("SF_PLANTING" 0 ((16719.45701 6862.74536) (16711.91742 6889.14027)))
("SF_PLANTING" 0 ((16745.85407 6930.61867) (16741.02511 6911.91301) (16711.91742 6889.14027)))
("SF_PLANTING" 0 ((16711.91742 6489.44186) (16862.74321 6489.44186)))
("SF_PLANTING" 0 ((16711.91742 6489.44186) (16708.29253 6530.91980) (16715.68439 6546.00328)))
("SF_ARCHITECTURE" 0 ((16711.91742 4521.11572) (16711.91742 4528.65803)))
("SF_ARCHITECTURE" 0 ((16730.76923 5705.12828) (16730.76923 4543.74016) (16711.91742 4528.65803)))
("SF_ARCHITECTURE" 0 ((16730.76923 4457.01357) (16730.76923 4506.03360) (16723.07353 4513.56844) (16711.91742
4521.11572)))
("SF_ARCHITECTURE" 0 ((16711.91742 4362.74468) (16711.91742 4336.35034)))
("SF_ARCHITECTURE" 0 ((16711.91742 4362.74468) (16730.76923 4381.59921) (16730.76923 4457.01357)))
("SF_ARCHITECTURE" 0 ((16711.91742 4336.35034) (16723.07353 4328.80181) (16730.76923 4317.49581) (16730.76923
3872.54943) (16723.22964 3842.38269)))
("SF_MASONRY_AND_ARCH" 0 ((16907.99208 2179.48744) (16821.26697 2179.49367) (16798.64253 2183.25792) (16734.54186
2179.49367) (16711.91742 2183.25792)))
("SF_MASONRY_AND_ARCH" 0 ((16745.85407 1459.27602) (16711.91742 1463.04581)))
("SF_PLANTING" 0 ((16809.95475 6975.86753) (16768.47851 6976.92353) (16730.76923 6998.63948) (16715.68439 7017.34514)))
("SF_PLANTING" 0 ((16745.85407 6930.61867) (16734.53348 6948.41584) (16715.68439 6953.24310)))
("SF_PLANTING" 0 ((16715.68439 6840.12093) (16719.45701 6862.74536)))
("SF_PLANTING" 0 ((16715.68439 6757.16414) (16700.75158 6723.22749) (16701.80792 6696.98744) (16708.15170 6693.21652)
(16734.54186 6693.20995) (16753.39367 6700.60305)))
("SF_PLANTING" 0 ((16715.68439 6757.16414) (16753.39367 6760.93541)))
("SF_MASONRY_AND_ARCH" 0 ((16715.68439 2828.05430) (16742.08145 2824.28382)))
("SF_PLANTING" 0 ((16715.68439 471.34333) (16749.62104 467.57070)))
("SF_PLANTING" 0 ((16715.68439 471.34333) (16724.28462 497.73756) (16753.54140 535.44400) (16851.43100 629.71437)))
("SF_PLANTING" 0 ((16719.45701 6862.74536) (16745.85407 6867.56527) (16779.79072 6891.86131) (16806.18213 6896.68201)))
("SF_MASONRY_AND_ARCH" 0 ((16719.45701 1862.74536) (16734.54186 1862.74536)))
("SF_ARCHITECTURE" 0 ((16730.76923 3834.84163) (16723.22964 3842.38269)))
("SF_PLANTING" 0 ((16768.47851 6591.25215) (16763.50170 6568.62771) (16742.08145 6550.82975) (16726.99661 6549.77376)))
("SF_PLANTING" 0 ((16779.79072 256.41120) (16764.70588 245.25226) (16726.99661 245.09898)))
("SF_ARCHITECTURE" 0 ((16779.79072 3797.13382) (16776.02500 3849.92500) (16776.01120 5693.81572) (16772.09219
5704.07195) (16760.93326 5708.75068) (16730.76923 5705.12828)))
("SF_PLANTING" 0 ((16734.54186 6636.50102) (16744.79627 6621.41753) (16745.85407 6598.79310)))
("SF_PLANTING" 0 ((16734.54186 6636.50102) (16716.74219 6621.41753) (16709.35588 6595.17749) (16719.45701 6591.40656)
(16745.85407 6598.79310)))
("SF_PLANTING" 0 ((16734.54186 6636.50102) (16746.90079 6674.20814) (16757.16629 6685.52036)))
("SF_PLANTING" 0 ((16745.85407 6930.61867) (16798.64253 6943.12839) (16813.72738 6957.01357)))
("SF_PLANTING" 0 ((16768.47851 6591.25215) (16745.85407 6598.79310)))
("SF_PLANTING" 0 ((16749.62104 467.57070) (16753.39367 444.94627)))
("SF_PLANTING" 0 ((16760.93326 6715.68654) (16753.39367 6760.93541)))
("SF_PLANTING" 0 ((16783.55769 6779.78857) (16764.71278 6774.96210) (16753.39367 6760.93541)))
("SF_PLANTING" 0 ((16753.39367 6700.60305) (16757.16629 6685.52036)))
("SF_PLANTING" 0 ((16753.39367 6700.60305) (16753.39367 6708.14480) (16760.93326 6715.68654)))
("SF_MASONRY_AND_ARCH" 0 ((16866.51584 2104.07240) (16851.43100 2107.83665) (16753.39367 2107.84287)))
("SF_MASONRY_AND_ARCH" 0 ((16753.39367 1040.72398) (16753.54140 1021.86934) (16758.22127 1010.55713) (16772.24548
996.53145) (16783.55769 991.70532)))
("SF_PLANTING" 0 ((16753.39367 433.63405) (16753.39367 444.94627)))
("SF_PLANTING" 0 ((16779.79072 448.71889) (16753.39367 444.94627)))
("SF_PLANTING" 0 ((16753.39367 433.63405) (16767.42760 411.00962) (16774.96867 388.38518) (16779.79072 335.59672)))
("SF_PLANTING" 0 ((16757.16629 6685.52036) (16772.24548 6671.49367) (16783.55769 6666.66640)))
("SF_PLANTING" 0 ((16779.79072 263.95079) (16765.91007 275.26301) (16757.16629 312.97229)))
("SF_PLANTING" 0 ((16757.16629 312.97229) (16772.09910 321.56278) (16779.79072 335.59672)))
("SF_PLANTING" 0 ((16760.93326 6817.49649) (16779.79072 6817.49649)))
("SF_PLANTING" 0 ((16779.79072 6715.68654) (16760.93326 6715.68654)))
("SF_MASONRY_AND_ARCH" 0 ((16941.92873 1862.74536) (16926.84955 1858.97410) (16889.14027 1862.74536) (16806.18213
1862.59762) (16791.10294 1858.98722) (16760.93326 1862.74536)))
("SF_PLANTING" 0 ((16760.93326 723.98190) (16809.95475 723.98190)))
("SF_MASONRY_AND_ARCH" 0 ((16764.70588 2428.35622) (16776.01810 2417.19864) (16836.35181 2417.04400)))
("SF_MASONRY_AND_ARCH" 0 ((16764.70588 2428.35622) (16768.47851 2435.89717)))
("SF_PLANTING" 0 ((16768.47851 6591.25215) (16786.12613 6606.33484) (16791.10294 6647.81324)))
("SF_PLANTING" 0 ((16772.24548 765.46097) (16794.86991 772.99570) (17006.02670 772.84729) (17016.28948 761.68835)
(17017.34729 727.75170)))
("SF_MASONRY_AND_ARCH" 0 ((16776.01810 3299.39695) (16772.25928 3288.08473) (16776.01810 3273.00124)))
("SF_MASONRY_AND_ARCH" 0 ((17006.03507 3276.77251) (16813.72738 3276.76629) (16776.01810 3273.00124)))
("SF_PLANTING" 0 ((16783.55769 6779.78857) (16779.79072 6817.49649)))
("SF_PLANTING" 0 ((16779.79072 6817.49649) (16787.33722 6832.57262) (16813.72738 6851.43314)))
("SF_PLANTING" 0 ((16791.10294 6689.29084) (16789.89740 6704.37398) (16779.79072 6715.68654)))
("SF_PLANTING" 0 ((16779.79072 6715.68654) (16791.10294 6723.22749)))
("SF_ARCHITECTURE" 0 ((16779.79072 3797.13382) (16802.41516 3793.36391) (17104.07240 3793.37014) (17126.69683
3797.13382) (17217.19457 3793.37014) (17236.04638 3797.13382)))
("SF_PLANTING" 0 ((16809.95475 723.98190) (16808.75057 712.66968) (16802.40679 705.28258) (16779.79072 697.58767)))
("SF_PLANTING" 0 ((16806.18213 324.28450) (16779.79072 335.59672)))
("SF_PLANTING" 0 ((16779.79072 263.95079) (16787.33032 260.18100) (16787.33032 256.41120)))
("SF_PLANTING" 0 ((16779.79072 256.41120) (16779.79072 263.95079)))
("SF_PLANTING" 0 ((16779.79072 256.41120) (16787.33032 256.41120)))
("SF_PLANTING" 0 ((16843.89140 6777.90373) (16783.55769 6779.78857)))
("SF_PLANTING" 0 ((16791.10294 6647.81324) (16784.75633 6655.36075) (16783.55769 6666.66640)))
("SF_PLANTING" 0 ((16791.10294 6677.97862) (16783.55769 6666.66640)))
("SF_MASONRY_AND_ARCH" 0 ((16847.66403 2556.56109) (16836.35181 2560.18382) (16783.55769 2560.33156)))
("SF_PLANTING" 0 ((16787.33032 7013.57466) (16797.43835 7009.64932) (16803.60407 6987.33416) (16809.95475 6983.40848)))
("SF_PLANTING" 0 ((16794.86991 256.41120) (16787.33032 256.41120)))
("SF_PLANTING" 0 ((16821.26697 6651.58371) (16791.10294 6647.81324)))
("SF_ARCHITECTURE" 0 ((16791.10294 5754.14774) (16787.33032 5757.91855) (16791.10294 5769.23077)))
("SF_MASONRY_AND_ARCH" 0 ((16794.86991 2956.25916) (16791.10294 2948.71821)))
("SF_PLANTING" 0 ((16817.49434 829.56165) (16791.10294 825.79186)))
("SF_PLANTING" 0 ((16794.86991 256.41120) (16806.18213 249.02342) (16828.80656 248.86878)))
("SF_PLANTING" 0 ((16794.86991 256.41120) (16802.41516 271.49321)))
("SF_MASONRY_AND_ARCH" 0 ((16821.26697 3103.31799) (16809.95475 3106.93462) (16798.64253 3103.31799)))
("SF_MASONRY_AND_ARCH" 0 ((16968.32579 1681.75057) (16957.01357 1675.41301) (16813.72738 1678.12636) (16799.84672
1685.66878) (16798.64253 1708.14480)))
("SF_MASONRY_AND_ARCH" 0 ((16806.18213 1602.56505) (16802.41516 1640.27149)))
("SF_MASONRY_AND_ARCH" 0 ((16889.14027 991.70532) (16840.11878 991.85238) (16828.80656 995.17896) (16802.41516
991.70532)))
("SF_PLANTING" 0 ((16802.41516 271.49321) (16806.18213 324.28450)))
("SF_PLANTING" 0 ((16802.41516 271.49321) (16809.96165 272.69808) (16836.35181 290.34785)))
("SF_PLANTING" 0 ((16809.95475 6983.40848) (16829.10351 7002.41075) (16823.84095 7021.11640) (16814.78235 7032.42862)
(16806.18213 7055.05305)))
("SF_PLANTING" 0 ((16813.72738 6851.43314) (16806.18213 6896.68201)))
("SF_PLANTING" 0 ((16840.11878 6938.15962) (16828.65328 6911.77127) (16806.18213 6896.68201)))
("SF_MASONRY_AND_ARCH" 0 ((16806.18213 1602.56505) (16817.49434 1598.79242)))
("SF_PLANTING" 0 ((16836.35181 328.05430) (16806.18213 324.28450)))
("SF_PLANTING" 0 ((16809.95475 6975.86753) (16809.95475 6983.40848)))
("SF_PLANTING" 0 ((16809.95475 6975.86753) (16813.72738 6957.01357)))
("SF_MASONRY_AND_ARCH" 0 ((16832.57919 2960.03043) (16809.95475 2956.25916)))
("SF_MASONRY_AND_ARCH" 0 ((16809.95475 2439.66844) (16825.03959 2443.43891)))
("SF_PLANTING" 0 ((16855.20362 731.52432) (16809.95475 723.98190)))
("SF_PLANTING" 0 ((16809.95475 441.17647) (16825.03959 436.34955) (16836.35181 426.09446)))
("SF_PLANTING" 0 ((16813.72738 6957.01357) (16821.27387 6955.80928) (16840.11878 6938.15962)))
("SF_PLANTING" 0 ((16847.66403 6851.43314) (16813.72738 6851.43314)))
("SF_PLANTING" 0 ((16843.89140 6606.33484) (16821.26697 6651.58371)))
("SF_PLANTING" 0 ((16821.26697 6651.58371) (16832.57919 6685.52036)))
("SF_PLANTING" 0 ((16825.03959 6696.83258) (16832.57919 6685.52036)))
("SF_PLANTING" 0 ((16825.03959 6595.02262) (16843.89140 6606.33484)))
("SF_PLANTING" 0 ((16836.35181 6447.96380) (16825.03959 6406.48575)))
("SF_MASONRY_AND_ARCH" 0 ((16825.03959 2043.74084) (16866.51584 2047.51131)))
("SF_MASONRY_AND_ARCH" 0 ((16825.03959 1813.72455) (16855.20362 1821.26075) (16979.63801 1821.26075) (17024.88688
1817.49717)))
("SF_PLANTING" 0 ((16843.89140 6734.53971) (16828.80656 6730.76923)))
("SF_PLANTING" 0 ((16836.35181 6542.23201) (16828.80656 6538.46154)))
("SF_PLANTING" 0 ((16919.30430 245.09898) (16904.21674 231.21900) (16866.51584 226.39208) (16836.49819 234.84242)
(16828.80656 248.86878)))
("SF_PLANTING" 0 ((16828.80656 248.86878) (16847.36154 271.49321) (16842.70113 286.42195) (16836.35181 290.34785)))
("SF_PLANTING" 0 ((16832.57919 6685.52036) (16862.74321 6685.52036)))
("SF_PLANTING" 0 ((16840.11878 6342.38303) (16832.57919 6327.30023)))
("SF_MASONRY_AND_ARCH" 0 ((16866.51584 1549.77376) (16870.13925 1538.46154) (16866.81131 1504.52489) (16869.99152
1493.21267) (16865.31165 1470.73665) (16851.43100 1463.19423) (16832.57919 1463.04581)))
("SF_PLANTING" 0 ((16836.35181 6542.23201) (16858.97624 6523.37885)))
("SF_PLANTING" 0 ((16836.35181 6542.23201) (16843.89830 6552.33993) (16870.28846 6553.54423)))
("SF_PLANTING" 0 ((16836.35181 335.59672) (16826.24231 346.90894) (16825.04367 354.44853) (16836.20260 407.23982)
(16836.35181 426.09446)))
("SF_PLANTING" 0 ((16836.35181 426.09446) (16889.14027 452.48869)))
("SF_PLANTING" 0 ((16836.35181 328.05430) (16836.35181 335.59672)))
("SF_PLANTING" 0 ((16892.91290 403.47002) (16874.20600 392.15023) (16854.00781 354.44853) (16836.35181 335.59672)))
("SF_PLANTING" 0 ((16836.35181 328.05430) (16836.35181 290.34785)))
("SF_PLANTING" 0 ((16902.33597 6932.50351) (16840.11878 6938.15962)))
("SF_PLANTING" 0 ((16843.89140 6777.90373) (16889.14027 6776.01810)))
("SF_PLANTING" 0 ((16843.89140 6777.90373) (16843.89140 6734.53971)))
("SF_PLANTING" 0 ((16847.66403 6843.89140) (16844.03914 6836.34310) (16843.89140 6777.90373)))
("SF_PLANTING" 0 ((16862.74321 6715.68654) (16843.89140 6734.53971)))
("SF_PLANTING" 0 ((16866.51584 6606.33484) (16843.89140 6606.33484)))
("SF_PLANTING" 0 ((16847.66403 6851.43314) (16847.66403 6843.89140)))
("SF_PLANTING" 0 ((16847.66403 6851.43314) (16876.77172 6885.51731) (16890.19943 6919.30939) (16902.33597 6932.50351)))
("SF_PLANTING" 0 ((16847.66403 6843.89140) (16870.28846 6836.49796) (16889.14027 6836.34966)))
("SF_PLANTING" 0 ((16855.20362 6233.03167) (16862.74321 6259.42692)))
("SF_MASONRY_AND_ARCH" 0 ((16855.20362 3099.54751) (16911.76471 3103.31799)))
("SF_PLANTING" 0 ((16858.97624 7002.26244) (16858.97624 6979.63801)))
("SF_PLANTING" 0 ((16862.74321 6489.44186) (16858.97624 6523.37885)))
("SF_PLANTING" 0 ((16870.28846 6553.54423) (16865.32557 6530.92670) (16858.97624 6523.37885)))
("SF_PLANTING" 0 ((16858.97624 6463.04683) (16862.74321 6489.44186)))
("SF_PLANTING" 0 ((16877.82805 6368.77828) (16860.03122 6391.40271) (16866.50894 6421.56855) (16865.32002 6428.95554)
(16858.97624 6432.88077)))
("SF_PLANTING" 0 ((16862.74321 6715.68654) (16885.36765 6715.68654)))
("SF_PLANTING" 0 ((16862.74321 6715.68654) (16862.74321 6685.52036)))
("SF_PLANTING" 0 ((16866.51584 6681.74989) (16862.74321 6685.52036)))
("SF_PLANTING" 0 ((16866.51584 6681.74989) (16862.74321 6681.74989) (16862.74321 6685.52036)))
("SF_PLANTING" 0 ((16975.86538 6489.44186) (16915.53733 6485.67127) (16862.74321 6489.44186)))
("SF_MASONRY_AND_ARCH" 0 ((16870.28846 2967.57138) (16862.74321 2956.25916)))
("SF_PLANTING" 0 ((16866.51584 6606.33484) (16870.28009 6617.64706) (16863.94186 6670.43733) (16866.51584 6681.74989)))
("SF_PLANTING" 0 ((16866.51584 6681.74989) (16885.36765 6681.90430) (16895.47715 6689.29774) (16895.62489 6700.60305)
(16885.36765 6715.68654)))
("SF_PLANTING" 0 ((16866.51584 6606.33484) (16876.77172 6587.48088) (16877.82805 6572.39819)))
("SF_PLANTING" 0 ((16866.51584 6293.36357) (16863.94186 6300.91154) (16873.90905 6334.84163) (16877.82805 6368.77828)))
("SF_MASONRY_AND_ARCH" 0 ((17160.63348 3469.07998) (17153.08552 3469.07998) (17104.07240 3469.07998) (16877.82805
3469.07998) (16866.51584 3469.07998)))
("SF_MASONRY_AND_ARCH" 0 ((16877.82805 3525.64129) (16870.44174 3510.55781) (16866.51584 3469.07998)))
("SF_MASONRY_AND_ARCH" 0 ((16866.51584 2779.03473) (16877.82805 2779.03473) (17051.28394 2779.03473) (17070.13575
2779.03473) (17088.98756 2779.03473) (17175.71833 2779.03473)))
("SF_MASONRY_AND_ARCH" 0 ((16870.28846 2760.18100) (16866.51584 2779.03473)))
("SF_MASONRY_AND_ARCH" 0 ((16866.51584 2639.51708) (16896.67986 2631.97613)))
("SF_MASONRY_AND_ARCH" 0 ((16866.51584 2639.51708) (16870.28846 2714.93213)))
("SF_MASONRY_AND_ARCH" 0 ((16870.28846 2070.13575) (16866.51584 2104.07240)))
("SF_MASONRY_AND_ARCH" 0 ((16866.51584 2104.07240) (16877.82805 2111.45950) (16911.76471 2115.38462)))
("SF_MASONRY_AND_ARCH" 0 ((16870.28846 2013.57466) (16866.51584 2047.51131)))
("SF_MASONRY_AND_ARCH" 0 ((16866.51584 2047.51131) (16870.28846 2058.82353)))
("SF_MASONRY_AND_ARCH" 0 ((16866.51584 1549.77376) (16870.65577 1594.80238) (16881.59514 1598.64819) (16907.99208
1595.03507) (16957.01357 1598.79242)))
("SF_MASONRY_AND_ARCH" 0 ((16866.51584 1255.65611) (16877.82805 1240.57410)))
("SF_PLANTING" 0 ((16870.28846 6553.54423) (16871.48428 6568.47285) (16877.82805 6572.39819)))
("SF_MASONRY_AND_ARCH" 0 ((16889.14027 3340.87455) (16870.28846 3344.64581)))
("SF_MASONRY_AND_ARCH" 0 ((16870.28846 2967.57138) (16866.52828 2990.19581) (16870.28846 3001.50803)))
("SF_MASONRY_AND_ARCH" 0 ((17183.25792 2971.34265) (17119.15724 2963.80713) (17077.67534 2967.41674) (17055.05090
2963.80090) (17032.42647 2967.56516) (16870.28846 2967.57138)))
("SF_MASONRY_AND_ARCH" 0 ((16870.28846 2922.32251) (16870.28846 2903.46934)))
("SF_MASONRY_AND_ARCH" 0 ((17179.48529 2895.92760) (17160.63348 2899.69808) (17073.90837 2899.69186) (17055.05090
2895.94072) (17002.26244 2899.54344) (16987.17760 2896.08224) (16972.09842 2899.69186) (16881.60068 2899.84581)
(16870.28846 2903.46934)))
("SF_MASONRY_AND_ARCH" 0 ((16870.28846 2722.47387) (16870.28846 2714.93213)))
("SF_MASONRY_AND_ARCH" 0 ((16949.47398 2722.47387) (16870.28846 2714.93213)))
("SF_MASONRY_AND_ARCH" 0 ((16870.28846 2560.33156) (16892.91290 2556.56109)))
("SF_MASONRY_AND_ARCH" 0 ((16889.14027 2420.81448) (16870.28846 2409.50226)))
("SF_MASONRY_AND_ARCH" 0 ((16870.28846 2013.57466) (16885.36765 2009.80419)))
("SF_MASONRY_AND_ARCH" 0 ((16870.28846 2013.57466) (16870.28846 1987.17975)))
("SF_MASONRY_AND_ARCH" 0 ((16870.28846 1957.01357) (16870.28846 1968.32579)))
("SF_MASONRY_AND_ARCH" 0 ((16870.28846 1957.01357) (16923.07692 1953.24287) (16934.38914 1953.24287) (16979.63111
1953.24287) (16987.17760 1953.24287)))
("SF_PLANTING" 0 ((16870.28846 829.56165) (16870.43484 863.49830) (16879.03224 889.89536) (16892.91290 901.05226)
(16941.92873 901.20758)))
("SF_MASONRY_AND_ARCH" 0 ((16877.82805 3525.64129) (16874.05543 3536.95351)))
("SF_MASONRY_AND_ARCH" 0 ((16889.14027 2420.81448) (16884.17183 2435.74253) (16874.05543 2439.66844)))
("SF_MASONRY_AND_ARCH" 0 ((17183.25792 1334.84163) (16949.47398 1334.69389) (16930.76708 1329.86697) (16921.88111
1312.37183) (16911.76471 1308.45362) (16877.98133 1309.65079) (16874.05543 1327.29921)))
("SF_MASONRY_AND_ARCH" 0 ((16881.60068 1331.07183) (16874.05543 1327.29921)))
("SF_MASONRY_AND_ARCH" 0 ((17179.48529 1187.78281) (17160.63348 1191.55260) (17107.84502 1191.40554) (17092.76018
1187.78903) (17070.13575 1191.25090) (17051.28394 1184.01923) (16874.05543 1187.78281)))
("SF_MASONRY_AND_ARCH" 0 ((16877.82805 1240.57410) (16870.44174 1206.63744) (16874.05543 1187.78281)))
("SF_PLANTING" 0 ((16874.05543 554.29864) (16890.34446 497.73756) (16899.25667 486.42534) (16904.22511 467.57070)))
("SF_PLANTING" 0 ((16874.05543 275.26301) (16919.30430 271.49321)))
("SF_PLANTING" 0 ((16892.91290 6527.14932) (16895.61934 6542.23201) (16887.93609 6564.84989) (16877.82805 6572.39819)))
("SF_PLANTING" 0 ((16885.36765 6372.54910) (16877.82805 6368.77828)))
("SF_MASONRY_AND_ARCH" 0 ((17183.25792 3525.64106) (17171.94570 3525.64106) (16877.82805 3525.64129)))
("SF_MASONRY_AND_ARCH" 0 ((16877.82805 1240.57410) (16915.53733 1236.80837) (17055.05090 1236.65441) (17070.13575
1233.03790) (17168.17308 1236.79661) (17183.25792 1233.03167)))
("SF_PLANTING" 0 ((16889.14027 6738.31097) (16885.36765 6715.68654)))
("SF_PLANTING" 0 ((16889.14027 6836.34966) (16894.11561 6802.41301) (16904.22511 6787.33032)))
("SF_PLANTING" 0 ((16889.14027 6836.34966) (16900.45249 6847.66188)))
("SF_PLANTING" 0 ((16889.14027 6738.31097) (16889.14027 6776.01810)))
("SF_PLANTING" 0 ((16889.14027 6776.01810) (16904.22511 6787.33032)))
("SF_PLANTING" 0 ((16889.14027 6738.31097) (16919.30430 6734.53971)))
("SF_MASONRY_AND_ARCH" 0 ((16889.14027 2420.81448) (17006.03507 2420.81448)))
("SF_MASONRY_AND_ARCH" 0 ((16889.14027 957.76867) (16889.14027 991.70532)))
("SF_MASONRY_AND_ARCH" 0 ((16896.67986 995.47511) (16889.14027 991.70532)))
("SF_MASONRY_AND_ARCH" 0 ((16889.14027 957.76867) (16937.94072 954.36550) (16943.13428 980.23778) (16949.47805
984.00826) (17070.13575 980.39932) (17092.76018 991.55000) (17179.48529 991.70532)))
("SF_PLANTING" 0 ((16892.91290 403.47002) (16892.76369 444.94140) (16889.14027 452.48869)))
("SF_PLANTING" 0 ((16904.22511 467.57070) (16889.14027 452.48869)))
("SF_PLANTING" 0 ((16892.91290 7051.28179) (16892.91290 7015.46029)))
("SF_PLANTING" 0 ((16892.91290 7051.28179) (16882.79649 7062.59434) (16876.77862 7081.44796) (16854.14729 7122.92636)
(16840.11878 7136.80452) (16828.96267 7136.80452) (16825.19287 7130.46075) (16826.09457 7111.61414) (16842.70113
7081.44796) (16860.17206 7028.66425) (16866.52274 7022.31391) (16892.91290 7015.46029)))
("SF_PLANTING" 0 ((16892.91290 7051.28179) (16910.70837 7077.67749) (16916.72624 7104.07240) (16936.95622 7138.00905)
(16949.47398 7171.94570)))
("SF_PLANTING" 0 ((16911.76471 6957.01357) (16897.88541 6968.32579) (16892.91290 7015.46029)))
("SF_PLANTING" 0 ((16930.61652 7017.34514) (16892.91290 7015.46029)))
("SF_PLANTING" 0 ((16900.45249 6847.66188) (16892.91290 6866.51584)))
("SF_PLANTING" 0 ((16900.45249 6440.42240) (16892.91290 6455.50520)))
("SF_MASONRY_AND_ARCH" 0 ((16892.91290 3427.60181) (16890.34446 3389.90090) (16896.68824 3383.55713) (16911.76471
3382.35294)))
("SF_MASONRY_AND_ARCH" 0 ((16892.91290 2594.26821) (16896.53348 2601.81686) (16896.67986 2631.97613)))
("SF_MASONRY_AND_ARCH" 0 ((16892.91290 2537.70713) (16892.91290 2511.31222)))
("SF_MASONRY_AND_ARCH" 0 ((17009.80204 2507.54174) (16994.72285 2511.30600) (16892.91290 2511.31222)))
("SF_PLANTING" 0 ((16892.91290 403.47002) (16900.45249 403.47002)))
("SF_MASONRY_AND_ARCH" 0 ((16904.22511 2635.74661) (16896.67986 2631.97613)))
("SF_PLANTING" 0 ((16930.61652 6843.89140) (16923.07002 6847.51403) (16900.45249 6847.66188)))
("SF_PLANTING" 0 ((16919.30430 290.34785) (16904.37839 309.19966) (16900.45249 403.47002)))
("SF_PLANTING" 0 ((16915.53733 414.78224) (16900.45249 403.47002)))
("SF_PLANTING" 0 ((16941.92873 6851.43314) (16921.87274 6911.76471) (16902.33597 6932.50351)))
("SF_PLANTING" 0 ((16902.33597 6932.50351) (16911.76471 6945.70136)))
("SF_PLANTING" 0 ((16911.76471 6787.33032) (16904.22511 6787.33032)))
("SF_PLANTING" 0 ((16915.53733 414.78224) (16915.38122 456.25848) (16904.22511 467.57070)))
("SF_MASONRY_AND_ARCH" 0 ((16907.99208 2179.48744) (16908.14129 2126.69683) (16911.76471 2115.38462)))
("SF_MASONRY_AND_ARCH" 0 ((16907.99208 2179.48744) (16919.30430 2186.87376) (16979.63801 2190.79966)))
("SF_PLANTING" 0 ((16911.76471 6957.01357) (16911.76471 6945.70136)))
("SF_PLANTING" 0 ((16911.76471 6957.01357) (16925.64400 6972.09627) (16930.61652 7017.34514)))
("SF_PLANTING" 0 ((17024.88688 6896.68201) (16960.78620 6925.79796) (16934.38914 6931.82296) (16919.31267 6944.49706)
(16911.76471 6945.70136)))
("SF_PLANTING" 0 ((16911.76471 6787.33032) (16925.79174 6779.63450) (16930.61652 6764.70588)))
("SF_PLANTING" 0 ((16911.76471 6787.33032) (16921.87274 6802.41301) (16930.61652 6843.89140)))
("SF_MASONRY_AND_ARCH" 0 ((16911.76471 2115.38462) (16926.84955 2111.91029) (16941.92873 2115.37771) (16960.78620
2111.91029) (16975.86538 2115.37839) (17107.84502 2115.37839) (17130.46946 2111.61414) (17168.17308 2115.08846)
(17179.48529 2111.61414)))
("SF_PLANTING" 0 ((16915.53733 414.78224) (16925.64400 407.23292) (16931.66742 361.99095) (16941.92873 343.13631)))
("SF_PLANTING" 0 ((16919.30430 6734.53971) (16934.53688 6696.83258) (16945.70136 6686.57636) (16964.55317 6677.97862)))
("SF_PLANTING" 0 ((16919.30430 6734.53971) (16930.61652 6764.70588)))
("SF_PLANTING" 0 ((16919.30430 290.34785) (16919.30430 271.49321)))
("SF_PLANTING" 0 ((16919.30430 290.34785) (16934.24140 301.66007) (16941.92873 316.74208)))
("SF_PLANTING" 0 ((16919.30430 271.49321) (16919.30430 245.09898)))
("SF_PLANTING" 0 ((17002.26244 252.63857) (16975.86538 230.16946) (16945.70136 231.07127) (16919.30430 245.09898)))
("SF_MASONRY_AND_ARCH" 0 ((16923.07692 3378.58247) (17032.42647 3378.58247) (17039.97172 3378.58247) (17066.36312
3374.81120)))
("SF_MASONRY_AND_ARCH" 0 ((16923.07692 3103.31799) (16938.16176 3099.54751) (16972.09005 3099.69525) (16979.63801
3103.31799)))
("SF_MASONRY_AND_ARCH" 0 ((17006.03507 3333.33360) (16968.32579 3340.72681) (16926.84955 3340.87455)))
("SF_PLANTING" 0 ((16930.61652 7017.34514) (16944.65192 7058.82353) (16957.01357 7119.15509)))
("SF_PLANTING" 0 ((16941.92873 6843.89140) (16930.61652 6843.89140)))
("SF_PLANTING" 0 ((16970.20928 6751.50803) (16930.61652 6764.70588)))
("SF_PLANTING" 0 ((16945.70136 6591.25215) (16944.64502 6610.10532) (16938.01810 6621.26312) (16930.61652 6625.18880)))
("SF_PLANTING" 0 ((16945.70136 6591.25215) (16941.92873 6587.48088) (16930.61652 6587.48088)))
("SF_MASONRY_AND_ARCH" 0 ((17028.65950 3050.52794) (16930.61652 3050.52794)))
("SF_PLANTING" 0 ((16934.38914 576.92308) (16953.24095 584.31708) (16972.09842 584.46550)))
("SF_PLANTING" 0 ((16941.92873 6851.43314) (17013.57466 6844.04627) (17043.73869 6866.51584)))
("SF_PLANTING" 0 ((16941.92873 6851.43314) (16941.92873 6843.89140)))
("SF_PLANTING" 0 ((16975.86538 6787.33032) (16952.18597 6832.57919) (16941.92873 6843.89140)))
("SF_PLANTING" 0 ((16941.92873 343.13631) (16941.92873 316.74208)))
("SF_PLANTING" 0 ((17009.80204 463.80090) (16995.91867 444.94627) (16993.51731 422.32183) (16976.01595 407.09208)
(16969.37523 395.92760) (16955.95724 350.82715) (16941.92873 343.13631)))
("SF_PLANTING" 0 ((16987.17760 335.59672) (16941.92873 316.74208)))
("SF_PLANTING" 0 ((16987.17760 6576.16867) (16968.32579 6590.19536) (16945.70136 6591.25215)))
("SF_MASONRY_AND_ARCH" 0 ((16945.70136 2631.97613) (16960.78620 2635.74661) (17028.65950 2635.59887) (17039.97172
2631.97613)))
("SF_MASONRY_AND_ARCH" 0 ((17036.19910 2609.35170) (16957.02048 2609.20396) (16949.47398 2605.58043)))
("SF_PLANTING" 0 ((17017.34729 727.75170) (16972.09842 727.90701) (16953.24095 735.29412)))
("SF_PLANTING" 0 ((17017.34729 7088.98971) (16964.41516 7037.40339) (16957.01357 7036.19910)))
("SF_MASONRY_AND_ARCH" 0 ((16957.01357 1598.79242) (16957.01357 1628.95928)))
("SF_MASONRY_AND_ARCH" 0 ((17122.92421 1587.48020) (17104.07240 1594.87489) (16957.01357 1598.79242)))
("SF_PLANTING" 0 ((16975.86538 6655.35419) (16964.55317 6677.97862)))
("SF_PLANTING" 0 ((16970.20928 6751.50803) (16974.66267 6700.60305) (16964.55317 6677.97862)))
("SF_PLANTING" 0 ((16975.86538 6489.44186) (16975.71900 6527.14932) (16968.32579 6542.23201)))
("SF_PLANTING" 0 ((16970.20928 6751.50803) (16990.95023 6746.00023) (17066.36312 6738.45882) (17232.27941 6738.31097)))
("SF_PLANTING" 0 ((16975.86538 6787.33032) (16968.54808 6760.86776) (16970.20928 6751.50803)))
("SF_PLANTING" 0 ((16998.48982 584.46550) (16972.09842 584.46550)))
("SF_PLANTING" 0 ((16972.09842 573.15328) (16972.09842 584.46550)))
("SF_PLANTING" 0 ((17217.19457 6787.33032) (16975.86538 6787.33032)))
("SF_PLANTING" 0 ((17239.81900 6481.90045) (17220.96719 6489.43529) (17066.36312 6485.67127) (17047.51131 6489.29367)
(16975.86538 6489.44186)))
("SF_MASONRY_AND_ARCH" 0 ((16979.63801 2281.29740) (16981.16256 2273.74943) (16975.86538 2262.44344)))
("SF_MASONRY_AND_ARCH" 0 ((17175.71833 2726.24434) (16979.63801 2726.24434)))
("SF_MASONRY_AND_ARCH" 0 ((16979.63801 2190.79966) (17017.34729 2190.79966)))
("SF_MASONRY_AND_ARCH" 0 ((16979.63801 2190.79966) (16979.63801 2202.11188) (16983.41063 2205.88235)))
("SF_MASONRY_AND_ARCH" 0 ((16983.41063 2239.81900) (16987.17760 2232.27726) (16983.41063 2224.73631)))
("SF_MASONRY_AND_ARCH" 0 ((16983.41063 1892.91075) (16983.41063 1900.45249)))
("SF_MASONRY_AND_ARCH" 0 ((16983.41063 1858.97410) (16990.95023 1858.97410)))
("SF_MASONRY_AND_ARCH" 0 ((16994.72285 1674.20814) (16983.41063 1674.20814)))
("SF_PLANTING" 0 ((16987.17760 335.59672) (16983.41063 358.22115)))
("SF_PLANTING" 0 ((16987.17760 7028.65735) (16966.80962 6968.32579) (16979.63801 6957.17500) (16994.72285 6960.78405)))
("SF_MASONRY_AND_ARCH" 0 ((17183.25792 1953.24287) (17171.94570 1953.24287) (17055.05090 1953.24287) (17039.97172
1953.24287) (16994.72692 1953.24287) (16987.17760 1953.24287)))
("SF_MASONRY_AND_ARCH" 0 ((16987.17760 1938.15962) (16987.17760 1953.24287)))
("SF_PLANTING" 0 ((16987.17760 335.59672) (16994.72285 335.59672)))
("SF_PLANTING" 0 ((16990.95023 380.84559) (16990.95023 392.15781)))
("SF_PLANTING" 0 ((17024.88688 6896.68201) (17023.68269 6945.70136) (17013.57466 6955.80928) (16994.72285 6960.78405)))
("SF_PLANTING" 0 ((16998.48982 6979.63801) (16994.72285 6960.78405)))
("SF_PLANTING" 0 ((17002.26244 252.63857) (16983.57081 279.03563) (16994.57364 320.51188) (16994.72285 335.59672)))
("SF_PLANTING" 0 ((17062.59615 392.15781) (17051.43032 384.46697) (17024.73914 351.73507) (16994.72285 335.59672)))
("SF_PLANTING" 0 ((17013.57466 252.63857) (17002.26244 252.63857)))
("SF_MASONRY_AND_ARCH" 0 ((17006.03507 3333.33360) (17006.03507 3276.77251)))
("SF_MASONRY_AND_ARCH" 0 ((17006.03507 3333.33360) (17024.88688 3336.94943) (17058.82353 3333.48133) (17073.90837
3337.09717) (17092.76018 3333.48133) (17168.17308 3333.33982) (17183.25792 3337.10407)))
("SF_MASONRY_AND_ARCH" 0 ((17006.03507 3276.77251) (17032.42647 3254.30271) (17168.17308 3254.14186) (17183.25792
3250.37681)))
("SF_MASONRY_AND_ARCH" 0 ((17009.80204 2507.54174) (17006.03507 2488.68778)))
("SF_MASONRY_AND_ARCH" 0 ((17024.88688 2417.04400) (17006.03507 2420.81448)))
("SF_MASONRY_AND_ARCH" 0 ((17134.23643 2450.98066) (17017.35136 2450.82602) (17011.00758 2447.05475) (17006.03507
2420.81448)))
("SF_MASONRY_AND_ARCH" 0 ((17009.80204 2507.54174) (17028.65950 2511.30600) (17175.71833 2511.31222)))
("SF_MASONRY_AND_ARCH" 0 ((17009.80204 1432.88179) (17009.80204 1417.79695)))
("SF_MASONRY_AND_ARCH" 0 ((17009.80204 1432.88179) (17047.51131 1436.64536) (17138.00905 1436.65158)))
("SF_PLANTING" 0 ((17062.59423 6994.72070) (17036.19910 6994.57285) (17013.57466 6983.40848)))
("SF_PLANTING" 0 ((17013.57466 252.63857) (17039.97172 230.16946) (17156.86086 228.95848) (17174.51278 214.93213)
(17171.94570 180.99548)))
("SF_PLANTING" 0 ((17013.57466 252.63857) (17024.88688 271.49321)))
("SF_MASONRY_AND_ARCH" 0 ((17017.34729 1380.09050) (17017.34729 1365.00848)))
("SF_PLANTING" 0 ((17126.69683 723.98190) (17111.61199 727.74683) (17017.34729 727.75170)))
("SF_PLANTING" 0 ((17032.42647 554.29864) (17027.45396 535.44400) (17017.34729 524.13179)))
("SF_MASONRY_AND_ARCH" 0 ((17021.11425 3099.54751) (17081.44796 3099.54751)))
("SF_PLANTING" 0 ((17021.11425 822.02206) (17062.59615 814.47964) (17115.38462 814.62738) (17179.48529 822.02206)))
("SF_PLANTING" 0 ((17043.73869 6881.59853) (17024.88688 6896.68201)))
("SF_PLANTING" 0 ((17122.92421 411.00962) (17111.76120 403.46244) (17058.82353 343.14389) (17041.16753 331.67081)
(17029.71448 309.19966) (17024.88688 271.49321)))
("SF_PLANTING" 0 ((17047.51131 275.26301) (17024.88688 271.49321)))
("SF_MASONRY_AND_ARCH" 0 ((17028.65950 3050.52794) (17028.65950 3069.38133)))
("SF_MASONRY_AND_ARCH" 0 ((17028.65950 3050.52794) (17179.48529 3050.52794)))
("SF_PLANTING" 0 ((17062.59615 599.54751) (17054.90452 584.61256) (17036.19910 573.15328)))
("SF_PLANTING" 0 ((17043.73869 6881.59853) (17043.73869 6866.51584)))
("SF_PLANTING" 0 ((17043.73869 6881.59853) (17061.39061 6900.45249) (17062.59615 6919.30645)))
("SF_PLANTING" 0 ((17043.73869 6866.51584) (17077.67534 6848.71210) (17115.38462 6847.66188)))
("SF_MASONRY_AND_ARCH" 0 ((17043.73869 2417.04400) (17092.76018 2417.04400)))
("SF_PLANTING" 0 ((17047.51131 275.26301) (17055.05090 271.49321)))
("SF_PLANTING" 0 ((17047.51131 275.26301) (17052.48665 294.11765) (17081.44796 319.31471) (17096.53281 324.28450)))
("SF_PLANTING" 0 ((17062.59423 7616.89287) (17062.59423 7017.34548) (17062.59423 7006.03292)))
("SF_ARCHITECTURE" 0 ((17062.59423 7616.89287) (17072.70283 7628.20520) (17073.90000 7635.74661) (17072.70283
7647.05882) (17062.59615 7654.60034)))
("SF_PLANTING" 0 ((17062.59423 6994.72070) (17062.59423 7006.03292)))
("SF_PLANTING" 0 ((17171.94570 7077.67749) (17153.09389 7076.47975) (17107.99140 7039.96301) (17092.61244 7017.50000)
(17062.59423 7006.03292)))
("SF_PLANTING" 0 ((17062.59423 6994.72070) (17062.59423 6975.86753) (17062.59615 6919.30645)))
("SF_ARCHITECTURE" 0 ((17066.36312 7971.34242) (17062.60023 7956.25939) (17062.59615 7654.60034)))
("SF_PLANTING" 0 ((17119.15724 6941.93088) (17096.53281 6924.13292) (17062.59615 6919.30645)))
("SF_ARCHITECTURE" 0 ((17130.46946 8088.23529) (17121.73529 8054.29864) (17093.81652 8020.36188) (17091.55600
7982.65464) (17081.44796 7971.34242) (17066.36312 7971.34242)))
("SF_MASONRY_AND_ARCH" 0 ((17153.09389 1074.66063) (17141.78167 1078.28337) (17085.22059 1078.58575) (17073.90837
1082.20215)))
("SF_MASONRY_AND_ARCH" 0 ((17077.67534 1104.82749) (17073.90837 1082.20215)))
("SF_MASONRY_AND_ARCH" 0 ((17092.76018 2631.97613) (17077.67534 2631.97613)))
("SF_MASONRY_AND_ARCH" 0 ((17077.67534 1825.03744) (17085.22466 1821.41471) (17175.71833 1821.26697)))
("SF_PLANTING" 0 ((17077.67534 524.13179) (17096.53281 531.52647) (17175.71833 539.21663)))
("SF_PLANTING" 0 ((17077.67534 275.26301) (17107.84502 291.40351) (17119.15724 305.42986)))
("SF_MASONRY_AND_ARCH" 0 ((17179.48529 2009.80419) (17168.17308 2013.56154) (17153.09389 2009.95192) (17081.44796
2009.80419)))
("SF_PLANTING" 0 ((17104.07240 6972.09627) (17119.15724 6941.93088)))
("SF_PLANTING" 0 ((17179.48529 584.46550) (17160.63348 588.23529) (17107.84502 584.46550)))
("SF_MASONRY_AND_ARCH" 0 ((17130.46946 3103.31799) (17111.61199 3099.54751)))
("SF_PLANTING" 0 ((17115.38462 6847.66188) (17120.20396 6877.82805) (17138.00905 6900.45249)))
("SF_PLANTING" 0 ((17115.38462 6847.66188) (17153.09389 6847.81018) (17164.40611 6851.43314)))
("SF_PLANTING" 0 ((17119.15724 6941.93088) (17138.00905 6941.93088)))
("SF_MASONRY_AND_ARCH" 0 ((17134.23643 2417.04400) (17122.92421 2417.04400)))
("SF_MASONRY_AND_ARCH" 0 ((17122.92421 1587.48020) (17119.31052 1493.21267) (17123.08032 1485.67783) (17138.00905
1474.35803)))
("SF_MASONRY_AND_ARCH" 0 ((17179.48529 1595.02262) (17122.92421 1587.48020)))
("SF_MASONRY_AND_ARCH" 0 ((17126.69683 2631.97613) (17164.40611 2635.74661) (17179.48529 2631.97613)))
("SF_MASONRY_AND_ARCH" 0 ((17130.46946 3182.50351) (17130.46946 3152.33812)))
("SF_MASONRY_AND_ARCH" 0 ((17130.46946 3182.50351) (17156.86086 3186.27477) (17183.25792 3182.50351)))
("SF_MASONRY_AND_ARCH" 0 ((17130.46946 3129.71369) (17130.46946 3103.31799)))
("SF_MASONRY_AND_ARCH" 0 ((17145.54864 3095.77704) (17130.46946 3103.31799)))
("SF_MASONRY_AND_ARCH" 0 ((17179.48529 2609.35170) (17134.23643 2613.12217)))
("SF_MASONRY_AND_ARCH" 0 ((17134.23643 2417.04400) (17134.23643 2450.98066)))
("SF_MASONRY_AND_ARCH" 0 ((17141.78167 2488.68778) (17141.62557 2458.52851) (17134.23643 2450.98066)))
("SF_MASONRY_AND_ARCH" 0 ((17153.09389 2409.50226) (17134.23643 2417.04400)))
("SF_PLANTING" 0 ((17138.00905 6941.93088) (17138.00905 6900.45249)))
("SF_PLANTING" 0 ((17153.09389 6960.78405) (17149.16799 6949.47839) (17138.00905 6941.93088)))
("SF_PLANTING" 0 ((17156.86086 6896.68201) (17138.00905 6900.45249)))
("SF_MASONRY_AND_ARCH" 0 ((17138.00905 1436.65158) (17138.00905 1474.35803)))
("SF_MASONRY_AND_ARCH" 0 ((17153.09389 1481.90045) (17138.00905 1474.35803)))
("SF_MASONRY_AND_ARCH" 0 ((17175.71833 1436.65158) (17138.00905 1436.65158)))
("SF_PLANTING" 0 ((17153.09389 6960.78405) (17142.99129 6972.09627) (17145.54864 6983.40848)))
("SF_PLANTING" 0 ((17171.94570 7077.67749) (17171.79796 7062.59400) (17154.14887 7017.34514) (17153.09389 6998.49197)))
("SF_PLANTING" 0 ((17153.09389 6960.78405) (17164.40611 6960.78405)))
("SF_PLANTING" 0 ((17164.40611 6851.43314) (17156.86086 6896.68201)))
("SF_PLANTING" 0 ((17232.27941 6923.07692) (17213.42195 6926.84084) (17194.57014 6922.02749) (17156.86086 6896.68201)))
("SF_MASONRY_AND_ARCH" 0 ((17160.63348 3469.07998) (17179.48529 3469.07998)))
("SF_MASONRY_AND_ARCH" 0 ((17160.63348 3469.07998) (17160.63348 3484.16290) (17164.40611 3487.93337)))
("SF_PLANTING" 0 ((17209.65498 6964.55532) (17171.95260 6958.21131) (17164.40611 6960.78405)))
("SF_PLANTING" 0 ((17179.48529 6990.95023) (17164.40611 6960.78405)))
("SF_PLANTING" 0 ((17258.67081 6855.20362) (17239.81900 6847.81018) (17175.71833 6847.81018) (17164.40611 6851.43314)))
("SF_PLANTING" 0 ((17175.71833 731.52432) (17168.17308 727.75170)))
("SF_ARCHITECTURE" 0 ((17168.17308 -3.77070) (17187.03054 -3.77070) (17232.27941 -3.77070)))
("SF_ARCHITECTURE" 0 ((17168.17308 -3.77070) (17171.93880 15.08201) (17168.18145 45.24887) (17168.17308 135.74661)
(17171.94570 180.99548)))
("SF_PLANTING" 0 ((17171.94570 7077.67749) (17209.65498 7092.60532) (17217.04129 7091.55566) (17220.81109 7085.21188)
(17219.76719 7070.13575) (17184.44819 7009.80419) (17179.48529 6990.95023)))
("SF_MASONRY_AND_ARCH" 0 ((17183.25792 2816.74208) (17175.71833 2816.74208)))
("SF_PLANTING" 0 ((17262.44344 6987.17975) (17273.90339 7006.03292) (17321.71934 7051.28179) (17326.24310 7062.58744)
(17322.62104 7068.92489) (17300.15271 7065.30882) (17277.52828 7053.99661) (17205.88235 6995.77749) (17179.48529
6990.95023)))
("SF_ARCHITECTURE" 0 ((17236.04638 1089.74265) (17209.65498 1085.97285)))
("SF_PLANTING" 0 ((17217.19457 6787.33032) (17228.50679 6777.22240) (17239.81900 6776.01810)))
("SF_PLANTING" 0 ((17217.19457 6787.33032) (17224.74253 6793.67432) (17300.15271 6794.72376) (17330.31674 6787.33032)))
("SF_PLANTING" 0 ((17224.73416 3589.74333) (17239.81900 3582.20238)))
("SF_PLANTING" 0 ((17254.90385 6896.68201) (17243.59163 6897.88631) (17236.20249 6904.22986) (17232.27941 6923.07692)))
("SF_PLANTING" 0 ((17285.06787 6915.53518) (17277.51991 6925.79796) (17258.67081 6936.05385) (17232.27941 6923.07692)))
("SF_ARCHITECTURE" 0 ((19430.61652 -3.77070) (19407.99208 -3.77070) (17251.13122 -3.77070) (17232.27941 -3.77070)))
("SF_ARCHITECTURE" 0 ((17236.04638 180.99548) (17232.28348 169.68326) (17232.27941 -3.77070)))
("SF_PLANTING" 0 ((17262.44344 6987.17975) (17236.04638 6975.86753)))
("SF_PLANTING" 0 ((17334.08937 3740.57274) (17333.93326 3785.81538) (17330.16346 3792.15916) (17247.35860 3793.51176)
(17236.04638 3797.13382)))
("SF_PLANTING" 0 ((17239.81900 3887.63156) (17236.19559 3876.31934) (17236.04638 3797.13382)))
("SF_PLANTING" 0 ((17236.04638 1255.65611) (17247.35860 1254.59977) (17258.52443 1247.96663) (17277.67466 1221.86719)
(17307.69231 1199.09502)))
("SF_PLANTING" 0 ((17236.04638 1255.65611) (17236.04638 1172.70079)))
("SF_PLANTING" 0 ((17236.04638 1255.65611) (17236.19559 1285.81538) (17239.81900 1293.36256)))
("SF_PLANTING" 0 ((17296.38009 1165.15837) (17262.44344 1172.55238) (17236.04638 1172.70079)))
("SF_PLANTING" 0 ((17236.04638 1172.70079) (17236.19559 1142.54084) (17239.81900 1134.99152)))
("SF_PLANTING" 0 ((17236.04638 1089.74265) (17239.81900 1059.57862)))
("SF_PLANTING" 0 ((17236.04638 1089.74265) (17239.81900 1134.99152)))
("SF_PLANTING" 0 ((17266.21606 991.70532) (17236.04638 991.70532)))
("SF_PLANTING" 0 ((17236.04638 180.99548) (17232.27941 199.85011) (17236.04638 991.70532)))
("SF_PLANTING" 0 ((17239.81900 1059.57862) (17236.19559 1044.49378) (17236.04638 991.70532)))
("SF_ARCHITECTURE" 0 ((17236.04638 180.99548) (18951.73643 180.99548)))
("SF_PLANTING" 0 ((17239.81900 6481.90045) (17236.04638 6436.65158) (17239.81900 6195.32421)))
("SF_PLANTING" 0 ((17239.81900 6481.90045) (17277.52828 6489.44186)))
("SF_ARCHITECTURE" 0 ((19385.36765 5874.81154) (19374.05136 5863.80215) (19351.43100 5872.23179) (18691.55543
6195.17602) (17239.81900 6195.32421)))
("SF_ARCHITECTURE" 0 ((17239.81900 6195.32421) (17239.81900 5825.79186)))
("SF_ARCHITECTURE" 0 ((19506.03507 5822.02104) (19494.72285 5814.63428) (19445.70136 5814.47964) (19423.07692
5818.24389) (17458.52376 5818.25701) (17439.66629 5822.01448) (17296.38009 5822.02760) (17281.29525 5825.64378)
(17239.81900 5825.79186)))
("SF_ARCHITECTURE" 0 ((17239.81900 5750.37715) (17236.04638 5765.45995) (17239.81900 5825.79186)))
("SF_ARCHITECTURE" 0 ((17239.81900 5750.37715) (19464.55317 5750.37059) (19521.11425 5742.83552)))
("SF_ARCHITECTURE" 0 ((17239.81900 5750.37715) (17236.04638 5731.52330) (17239.80656 5678.73303) (17236.05475
5625.94276) (17239.81900 5610.85973)))
("SF_ARCHITECTURE" 0 ((17239.81900 5610.85973) (19377.82805 5610.85973)))
("SF_ARCHITECTURE" 0 ((17239.81900 4117.64706) (17236.04638 4132.73043) (17236.05475 5595.77636) (17239.81900
5610.85973)))
("SF_PLANTING" 0 ((17239.81900 4117.64706) (17266.21606 4117.64706)))
("SF_PLANTING" 0 ((17239.81900 4117.64706) (17239.81900 4083.71041)))
("SF_PLANTING" 0 ((17330.31674 4023.37817) (17303.91968 4038.60962) (17262.44344 4078.73541) (17239.81900 4083.71041)))
("SF_PLANTING" 0 ((17239.81900 4083.71041) (17236.04638 4072.39819) (17236.19559 3996.99005) (17239.81900 3989.44152)))
("SF_PLANTING" 0 ((17239.81900 3955.50486) (17239.81900 3989.44152)))
("SF_PLANTING" 0 ((17334.08937 3981.90045) (17307.69231 3990.64627) (17292.60747 4000.59977) (17239.81900 3989.44152)))
("SF_PLANTING" 0 ((17239.81900 3887.63156) (17236.04638 3910.25600) (17236.19559 3951.57998) (17239.81900 3955.50486)))
("SF_PLANTING" 0 ((17307.69231 3951.73495) (17288.84050 3966.65611) (17266.21606 3955.65984) (17239.81900 3955.50486)))
("SF_PLANTING" 0 ((17371.79299 3895.17387) (17349.16855 3884.00950) (17239.81900 3887.63156)))
("SF_PLANTING" 0 ((17239.81900 3012.82025) (17236.04638 3027.90373) (17236.05475 3242.83586) (17239.81900 3265.46029)
(17236.05475 3563.34842) (17239.81900 3582.20238)))
("SF_PLANTING" 0 ((17334.08937 3740.57274) (17329.26041 3718.10328) (17300.15271 3709.20271) (17286.11731 3691.55396)
(17270.13224 3642.53394) (17268.78032 3589.89796) (17239.81900 3582.20238)))
("SF_PLANTING" 0 ((17239.81900 3012.82025) (18981.90045 3009.04977)))
("SF_PLANTING" 0 ((17239.81900 3012.82025) (17236.04638 2993.96708) (17236.05475 2835.59604) (17239.81900 2824.28382)))
("SF_PLANTING" 0 ((19061.08597 2820.51256) (19046.00113 2816.74830) (18947.96380 2816.74830) (18929.11199 2820.50633)
(18378.58032 2820.51878) (18359.72851 2824.28360) (17239.81900 2824.28382)))
("SF_ARCHITECTURE" 0 ((17239.81900 1293.36256) (17236.04830 1304.67477) (17236.04830 1941.93088) (17236.04830
1964.55532) (17236.04830 2458.52161) (17236.04830 2477.37557) (17236.05475 2812.97161) (17239.81900 2824.28382)))
("SF_PLANTING" 0 ((17266.21606 1289.59276) (17239.81900 1293.36256)))
("SF_PLANTING" 0 ((17307.69231 1127.45192) (17277.52828 1134.84446) (17239.81900 1134.99152)))
("SF_PLANTING" 0 ((17239.81900 1059.57862) (17254.90385 1059.57862)))
("SF_PLANTING" 0 ((17254.90385 6896.68201) (17258.67081 6855.20362)))
("SF_PLANTING" 0 ((17254.90385 6896.68201) (17285.06787 6915.53518)))
("SF_PLANTING" 0 ((17254.90385 1059.57862) (17266.21606 1052.19084) (17300.15271 1052.18394) (17318.85124 1057.00464)
(17322.77715 1063.34842)))
("SF_PLANTING" 0 ((17307.69231 1127.45192) (17295.32376 1101.06244) (17267.26278 1078.28337) (17254.90385 1059.57862)))
("SF_PLANTING" 0 ((17258.67081 6855.20362) (17277.52828 6847.81018) (17303.91968 6847.66188)))
("SF_PLANTING" 0 ((17262.44344 6987.17975) (17281.29525 6972.09627)))
("SF_PLANTING" 0 ((17330.31674 4072.39819) (17311.46493 4077.21889) (17285.07477 4092.30814) (17266.21606 4117.64706)))
("SF_PLANTING" 0 ((17330.31674 4117.64706) (17307.69231 4118.70373) (17285.06787 4128.80464) (17277.52828 4127.75475)
(17266.21606 4117.64706)))
("SF_PLANTING" 0 ((17300.15271 1244.34389) (17278.57500 1266.96833) (17266.21606 1289.59276)))
("SF_PLANTING" 0 ((17266.21606 1289.59276) (17288.83213 1307.23495) (17295.32376 1304.51459) (17300.15271 1289.59276)))
("SF_PLANTING" 0 ((17379.33824 935.14423) (17330.31674 931.37161) (17266.21606 935.14423)))
("SF_PLANTING" 0 ((17281.29525 3921.56821) (17273.75566 3910.25600)))
("SF_ARCHITECTURE" 0 ((19396.67986 6489.44186) (19419.30430 6494.41686) (19429.41380 6504.52489) (19430.46324
6549.76719) (19419.30430 6560.02998) (19189.29299 6561.07941) (19170.43552 6557.46991) (19155.35633 6561.07941)
(18499.24774 6561.07941) (18465.31109 6557.31550) (18446.45362 6560.93767) (18397.43778 6560.93767) (18382.35984
6553.39638) (18374.96663 6542.23201) (18374.66414 6474.35905) (18371.18846 6463.04683) (18370.88744 6406.48575)
(18367.11482 6399.09876) (18355.95588 6395.18009) (18231.52149 6395.18009) (18220.36538 6399.09876) (18216.59559
6406.48575) (18216.28620 6542.23201) (18212.51640 6549.76719) (18201.35747 6557.31527) (17277.52828 6557.31550)))
("SF_PLANTING" 0 ((17277.52828 6489.44186) (17277.52828 6557.31550)))
("SF_PLANTING" 0 ((17330.31674 6787.33032) (17317.80871 6749.62975) (17288.84050 6730.62093) (17277.68156 6715.68654)
(17277.52828 6557.31550)))
("SF_ARCHITECTURE" 0 ((19396.67986 6489.44186) (19385.36765 6493.20611) (18446.45362 6493.05803) (18435.29751
6485.66471) (18431.52771 6478.12964) (18431.21833 6346.16041) (18423.82511 6337.71731) (18408.75000 6334.84163)
(18291.85520 6334.84819) (18273.00339 6338.59932) (18231.52149 6334.84819) (18159.88529 6339.81663) (18152.49208
6349.92466) (18152.18269 6478.12964) (18141.02376 6489.28710) (17277.52828 6489.44186)))
("SF_PLANTING" 0 ((17285.06787 6915.53518) (17307.69231 6926.84740)))
("SF_ARCHITECTURE" 0 ((18989.44005 2752.63925) (18857.46606 2752.64548) (18834.84163 2756.41052) (17300.15271
2756.40430) (17288.84050 2752.63925)))
("SF_PLANTING" 0 ((17315.23190 972.85068) (17307.68541 979.19446) (17288.84050 984.16290)))
("SF_ARCHITECTURE" 0 ((19434.38914 5690.04525) (17292.60747 5690.04525)))
("SF_PLANTING" 0 ((17307.69231 3951.73495) (17303.76640 3936.80622) (17292.60747 3932.88043)))
("SF_PLANTING" 0 ((17375.56561 6847.66188) (17303.91968 6847.66188)))
("SF_PLANTING" 0 ((17360.48077 6900.45249) (17356.55769 6894.10848) (17311.46900 6881.44412) (17304.07579 6870.28631)
(17303.91968 6847.66188)))
("SF_PLANTING" 0 ((17330.31674 6930.61867) (17319.00452 6923.23835) (17307.69231 6926.84740)))
("SF_PLANTING" 0 ((17322.77715 6941.93088) (17307.69231 6926.84740)))
("SF_PLANTING" 0 ((17307.69231 3951.73495) (17330.31674 3963.04717)))
("SF_PLANTING" 0 ((17307.69231 1127.45192) (17315.23190 1127.45192)))
("SF_PLANTING" 0 ((17315.23190 1127.45192) (17326.39774 1104.82749) (17322.77715 1063.34842)))
("SF_PLANTING" 0 ((17315.23190 1127.45192) (17326.54412 1134.99152)))
("SF_PLANTING" 0 ((17330.31674 6930.61867) (17330.31674 6938.15962) (17322.77715 6941.93088)))
("SF_PLANTING" 0 ((17326.54412 6953.24310) (17322.77715 6941.93088)))
("SF_PLANTING" 0 ((17322.77715 1172.70079) (17326.54412 1134.99152)))
("SF_PLANTING" 0 ((17379.33824 1070.89084) (17364.25339 1063.49683) (17322.77715 1063.34842)))
("SF_PLANTING" 0 ((17368.02602 1131.22172) (17326.54412 1134.99152)))
("SF_PLANTING" 0 ((17375.56561 6923.07692) (17356.71380 6930.47036) (17330.31674 6930.61867)))
("SF_PLANTING" 0 ((17330.31674 6787.33032) (17352.94118 6792.15102) (17371.63971 6806.18428) (17378.13959 6832.57919)
(17375.56561 6847.66188)))
("SF_PLANTING" 0 ((17330.31674 4117.64706) (17330.31674 4072.39819)))
("SF_ARCHITECTURE" 0 ((17330.31674 4117.64706) (17334.08937 4140.27149) (17330.32364 4170.43699) (17330.46448
5184.76663) (17341.63586 5202.41538) (17379.33824 5203.61991)))
("SF_PLANTING" 0 ((17337.85633 4027.14932) (17337.70305 4061.08597) (17330.31674 4072.39819)))
("SF_PLANTING" 0 ((17330.31674 4023.37817) (17334.08937 3981.90045)))
("SF_PLANTING" 0 ((17330.31674 4023.37817) (17337.85633 4027.14932)))
("SF_PLANTING" 0 ((17360.48077 3925.33937) (17338.01244 3936.65781) (17330.31674 3963.04717)))
("SF_PLANTING" 0 ((17334.08937 3981.90045) (17330.31674 3963.04717)))
("SF_PLANTING" 0 ((17560.33371 3740.57274) (17522.62443 3744.34389) (17488.68778 3740.57964) (17334.08937 3740.57274)))
("SF_PLANTING" 0 ((17349.16855 1274.51075) (17334.08937 1278.28054)))
("SF_PLANTING" 0 ((17334.08937 1278.28054) (17330.46448 1274.35543) (17331.37308 1233.03167) (17345.54796 1206.64231)
(17368.02602 1195.32523)))
("SF_ARCHITECTURE" 0 ((17334.08937 1278.28054) (17330.32364 1293.36256) (17330.32364 1376.32070) (17334.08937
1398.94514) (17334.08744 2217.19457) (17334.08744 2236.04853) (17334.08744 2349.17070) (17345.40158 2363.04921)
(17375.56561 2360.48292)))
("SF_PLANTING" 0 ((17337.85633 4027.14932) (17371.78891 4008.28914) (17378.13269 4000.75373) (17383.10520 3981.90045)))
("SF_PLANTING" 0 ((17371.79299 3895.17387) (17360.48077 3925.33937)))
("SF_PLANTING" 0 ((17375.56561 3944.19265) (17360.48077 3925.33937)))
("SF_PLANTING" 0 ((17368.02602 1195.32523) (17379.33824 1146.30373)))
("SF_PLANTING" 0 ((17368.02602 1195.32523) (17379.33824 1201.80916) (17398.19005 1202.86482)))
("SF_PLANTING" 0 ((17368.02602 1131.22172) (17372.99853 1101.05486) (17383.10520 1089.74265)))
("SF_PLANTING" 0 ((17368.02602 1131.22172) (17379.33824 1146.30373)))
("SF_ARCHITECTURE" 0 ((17371.79299 5663.65011) (17582.95814 5663.65011)))
("SF_PLANTING" 0 ((17371.79299 3895.17387) (17386.87783 3895.17387)))
("SF_PLANTING" 0 ((17375.56561 6923.07692) (17383.10520 6923.07692)))
("SF_PLANTING" 0 ((17375.56561 6923.07692) (17379.33824 6915.53518) (17383.10520 6923.07692)))
("SF_PLANTING" 0 ((17390.65045 6870.28631) (17389.44491 6862.73846) (17375.56561 6847.66188)))
("SF_PLANTING" 0 ((17375.56561 3944.19265) (17401.96267 3944.19265)))
("SF_PLANTING" 0 ((17375.56561 3944.19265) (17375.71335 3966.81708) (17383.10520 3981.90045)))
("SF_ARCHITECTURE" 0 ((17375.56561 2360.48292) (17405.72964 2360.48292)))
("SF_ARCHITECTURE" 0 ((17375.56561 2360.48292) (17379.33631 2266.21391) (17379.33631 2247.36075)))
("SF_PLANTING" 0 ((17375.56561 1346.15385) (17398.19005 1346.15385)))
("SF_PLANTING" 0 ((17375.56561 1274.51075) (17375.56561 1289.59276) (17375.56561 1338.60656) (17375.56561 1346.15385)))
("SF_PLANTING" 0 ((17390.65045 1402.71493) (17383.24887 1398.78982) (17375.56561 1383.86029) (17375.56561 1346.15385)))
("SF_PLANTING" 0 ((17375.56561 1274.51075) (17401.96267 1274.51075)))
("SF_PLANTING" 0 ((17375.56561 1274.51075) (17379.49152 1255.65611) (17383.26131 1248.41753) (17401.96267 1251.88631)))
("SF_ARCHITECTURE" 0 ((17379.33631 2247.36075) (17398.19005 2247.36075)))
("SF_ARCHITECTURE" 0 ((17390.65045 2190.79966) (17379.33631 2205.88235) (17379.33631 2239.81210) (17379.33631
2247.36075)))
("SF_ARCHITECTURE" 0 ((17405.72964 5203.61991) (17379.33824 5203.61991)))
("SF_ARCHITECTURE" 0 ((17390.65045 5090.49774) (17380.53405 5101.80995) (17375.71335 5116.89333) (17375.71335
5188.53654) (17379.33824 5203.61991)))
("SF_PLANTING" 0 ((17379.33824 4095.02262) (17398.19005 4095.02262)))
("SF_PLANTING" 0 ((17405.72964 4034.69038) (17383.25577 4042.38665) (17372.85079 4061.08597) (17371.94910 4083.71041)
(17379.33824 4095.02262)))
("SF_PLANTING" 0 ((17390.65045 4155.35486) (17379.49152 4150.52704) (17375.71889 4144.03575) (17375.71335 4106.33484)
(17379.33824 4095.02262)))
("SF_PLANTING" 0 ((17417.04186 1134.99152) (17409.49536 1141.33597) (17379.33824 1146.30373)))
("SF_PLANTING" 0 ((17379.33824 1070.89084) (17401.96267 1059.72636) (17443.43891 1059.57862)))
("SF_PLANTING" 0 ((17379.33824 1070.89084) (17383.10520 1089.74265)))
("SF_PLANTING" 0 ((17481.14819 937.02771) (17454.75113 934.08710) (17435.89932 926.09118) (17420.81448 934.98891)
(17379.33824 935.14423)))
("SF_PLANTING" 0 ((17394.41742 976.62048) (17380.54095 961.53846) (17379.33824 935.14423)))
("SF_PLANTING" 0 ((17409.50226 6919.30645) (17383.10520 6923.07692)))
("SF_PLANTING" 0 ((17409.50226 3974.35939) (17401.95430 3981.74581) (17383.10520 3981.90045)))
("SF_PLANTING" 0 ((17417.04186 1112.36708) (17383.10520 1089.74265)))
("SF_PLANTING" 0 ((17386.87783 3895.17387) (17394.42579 3888.82319) (17417.04186 3883.86165) (17443.43201 3888.82941)
(17450.97851 3895.17387)))
("SF_PLANTING" 0 ((17386.87783 3895.17387) (17401.96267 3929.11052)))
("SF_ARCHITECTURE" 0 ((17390.65045 5079.18552) (17390.65045 5090.49774)))
("SF_ARCHITECTURE" 0 ((17390.65045 5090.49774) (17405.57636 5109.35102) (17405.72964 5203.61991)))
("SF_ARCHITECTURE" 0 ((17390.65045 5079.18552) (17394.41742 5075.41437) (17390.65045 5071.64446)))
("SF_ARCHITECTURE" 0 ((17390.65045 5079.18552) (17390.65045 5071.64446)))
("SF_ARCHITECTURE" 0 ((17390.65045 5079.18552) (17386.87783 5079.18552) (17390.65045 5071.64446)))
("SF_ARCHITECTURE" 0 ((17390.65045 4155.35486) (17390.65045 5071.64446)))
("SF_PLANTING" 0 ((17390.65045 4155.35486) (17404.52692 4144.04197) (17409.35452 4121.41821) (17408.29808 4110.10600)
(17398.19005 4095.02262)))
("SF_ARCHITECTURE" 0 ((17390.65045 1402.71493) (17390.65045 2190.79966)))
("SF_ARCHITECTURE" 0 ((17390.65045 2190.79966) (17405.57636 2209.65283) (17405.57636 2236.04853) (17398.19005
2247.36075)))
("SF_PLANTING" 0 ((17390.65045 1402.71493) (17400.76403 1391.40271) (17405.58326 1376.32070) (17405.57636 1361.23586)
(17398.19005 1346.15385)))
("SF_PLANTING" 0 ((17394.41742 976.62048) (17405.72964 972.85068)))
("SF_PLANTING" 0 ((17394.41742 976.62048) (17403.01765 999.24491) (17417.04186 1013.12489) (17443.43891 1010.55713)))
("SF_PLANTING" 0 ((17405.72964 4034.69038) (17409.35452 4061.08597) (17404.67466 4083.71041) (17398.19005 4095.02262)))
("SF_ARCHITECTURE" 0 ((17405.72964 2360.48292) (17405.57636 2262.44344) (17398.19005 2247.36075)))
("SF_PLANTING" 0 ((17401.96267 1274.51075) (17405.57636 1334.84163) (17398.19005 1346.15385)))
("SF_PLANTING" 0 ((17420.81448 1187.78281) (17409.50916 1188.98767) (17398.19005 1202.86482)))
("SF_PLANTING" 0 ((17413.27489 1233.03167) (17398.19005 1202.86482)))
("SF_PLANTING" 0 ((17401.96267 3929.11052) (17401.96267 3944.19265)))
("SF_PLANTING" 0 ((17409.50226 3974.35939) (17401.96267 3944.19265)))
("SF_PLANTING" 0 ((17401.96267 3929.11052) (17443.43891 3929.11052)))
("SF_PLANTING" 0 ((17401.96267 1251.88631) (17401.96267 1274.51075)))
("SF_PLANTING" 0 ((17401.96267 1251.88631) (17408.30645 1247.96041) (17413.27489 1233.03167)))
("SF_ARCHITECTURE" 0 ((17405.72964 5203.61991) (17439.66629 5203.47183) (17450.97851 5199.84876)))
("SF_PLANTING" 0 ((17405.72964 4034.69038) (17409.50226 4012.06595)))
("SF_ARCHITECTURE" 0 ((17405.72964 2360.48292) (17439.66629 2360.33518) (17450.97851 2356.71165)))
("SF_PLANTING" 0 ((17409.50226 3974.35939) (17420.81448 3974.35939) (17424.58710 3978.12930)))
("SF_PLANTING" 0 ((17413.27489 4000.75373) (17424.58710 3978.12930)))
("SF_PLANTING" 0 ((17443.43891 1240.57410) (17413.27489 1233.03167)))
("SF_PLANTING" 0 ((17417.04186 1112.36708) (17417.04186 1134.99152)))
("SF_PLANTING" 0 ((17417.04186 1134.99152) (17439.66629 1146.30373)))
("SF_PLANTING" 0 ((17417.04186 1112.36708) (17435.89932 1111.31143) (17454.75113 1101.05486)))
("SF_PLANTING" 0 ((17439.66629 1165.15837) (17420.81448 1187.78281)))
("SF_PLANTING" 0 ((17450.97851 1229.26188) (17420.81448 1187.78281)))
("SF_PLANTING" 0 ((17450.97851 3981.90045) (17424.58710 3978.12930)))
("SF_PLANTING" 0 ((17439.66629 1165.15837) (17439.66629 1146.30373)))
("SF_PLANTING" 0 ((17492.46041 1202.86482) (17469.84005 1194.12658) (17439.66629 1165.15837)))
("SF_PLANTING" 0 ((17477.37557 1146.30373) (17462.29072 1142.53394) (17439.66629 1146.30373)))
("SF_PLANTING" 0 ((17450.97851 3895.17387) (17443.59219 3910.25600) (17443.43891 3929.11052)))
("SF_PLANTING" 0 ((17458.52376 3944.19265) (17443.43891 3929.11052)))
("SF_PLANTING" 0 ((17443.43891 1240.57410) (17450.97851 1229.26188)))
("SF_PLANTING" 0 ((17443.43891 1240.57410) (17447.21154 1266.96833)))
("SF_PLANTING" 0 ((17450.97851 1036.95419) (17443.43891 1059.57862)))
("SF_PLANTING" 0 ((17454.75113 1074.66063) (17443.43891 1059.57862)))
("SF_PLANTING" 0 ((17481.14819 991.70532) (17454.75113 998.35079) (17443.43891 1010.55713)))
("SF_PLANTING" 0 ((17450.97851 1036.95419) (17443.43891 1010.55713)))
("SF_PLANTING" 0 ((17447.21154 1266.96833) (17465.91007 1258.37025) (17475.49208 1242.45758)))
("SF_ARCHITECTURE" 0 ((17447.21154 1266.96833) (17447.42828 1300.75724) (17451.28100 1308.59446) (17450.97443
1787.33032) (17447.21154 1809.95475) (17447.35792 1858.97410) (17450.97443 1874.05758) (17447.21154 2171.94570)
(17450.97443 2194.57014) (17450.97851 2356.71165)))
("SF_ARCHITECTURE" 0 ((17450.97851 4155.35486) (17450.97851 5199.84876)))
("SF_ARCHITECTURE" 0 ((17503.77262 5199.84876) (17488.68778 5203.61991) (17450.97851 5199.84876)))
("SF_PLANTING" 0 ((17450.97851 4155.35486) (17466.06335 4151.58371)))
("SF_PLANTING" 0 ((17450.97851 4064.85713) (17443.43891 4113.87590) (17443.58665 4132.73043) (17450.97851 4155.35486)))
("SF_PLANTING" 0 ((17450.97851 4064.85713) (17458.38009 4060.93133) (17488.68778 4019.60826)))
("SF_PLANTING" 0 ((17450.97851 4064.85713) (17437.10204 4053.54423) (17436.94604 4012.06595) (17440.86493 4000.75441)
(17450.97851 3989.44152)))
("SF_PLANTING" 0 ((17450.97851 3981.90045) (17450.97851 3989.44152)))
("SF_PLANTING" 0 ((17450.97851 3989.44152) (17480.99762 4004.67296) (17488.68778 4019.60826)))
("SF_PLANTING" 0 ((17450.97851 3981.90045) (17457.47285 3966.81708) (17458.52376 3951.73495)))
("SF_PLANTING" 0 ((17450.97851 3895.17387) (17466.06335 3895.17387)))
("SF_ARCHITECTURE" 0 ((17503.77262 2356.71165) (17488.68778 2360.48292) (17450.97851 2356.71165)))
("SF_PLANTING" 0 ((17450.97851 1229.26188) (17466.12964 1234.30351) (17475.49208 1242.45758)))
("SF_PLANTING" 0 ((17488.68778 1003.01753) (17482.34400 1010.56471) (17477.01380 1036.58473) (17450.97851 1036.95419)))
("SF_PLANTING" 0 ((17530.16403 1108.59729) (17507.53959 1097.43348) (17454.75113 1101.05486)))
("SF_PLANTING" 0 ((17454.75113 1101.05486) (17454.75113 1074.66063)))
("SF_PLANTING" 0 ((17454.75113 1074.66063) (17469.83597 1069.69219) (17481.14819 1059.57862)))
("SF_PLANTING" 0 ((17458.52376 3944.19265) (17458.52376 3951.73495)))
("SF_PLANTING" 0 ((17522.62443 3944.19265) (17500.00000 3955.35701) (17458.52376 3951.73495)))
("SF_PLANTING" 0 ((17458.52376 3944.19265) (17468.63043 3936.64536) (17473.60294 3917.79830)))
("SF_PLANTING" 0 ((17462.29072 663.65102) (17481.14819 667.42081)))
("SF_PLANTING" 0 ((17466.06335 3895.17387) (17473.61131 3888.82941) (17492.46041 3884.00950) (17526.39706 3884.00950)
(17567.72002 3896.36459) (17571.64593 3902.71493)))
("SF_PLANTING" 0 ((17466.06335 3895.17387) (17473.60294 3917.79830)))
("SF_PLANTING" 0 ((17466.06335 614.62952) (17484.91516 618.40215)))
("SF_PLANTING" 0 ((17496.22738 3921.56821) (17473.60294 3917.79830)))
("SF_PLANTING" 0 ((17492.46041 1202.86482) (17487.63835 1221.71946) (17475.49208 1242.45758)))
("SF_PLANTING" 0 ((17475.49208 1242.45758) (17511.31222 1274.51075)))
("SF_PLANTING" 0 ((17477.37557 1146.30373) (17481.14819 1153.84615) (17486.80430 1148.19005)))
("SF_PLANTING" 0 ((17477.37557 1146.30373) (17486.80430 1148.19005)))
("SF_PLANTING" 0 ((17481.14819 937.02771) (17481.14819 991.70532)))
("SF_PLANTING" 0 ((17488.68778 1003.01753) (17481.14819 991.70532)))
("SF_PLANTING" 0 ((17481.14819 937.02771) (17481.29457 886.12274) (17484.91516 874.81052)))
("SF_PLANTING" 0 ((17481.14819 937.02771) (17526.39706 946.45645)))
("SF_PLANTING" 0 ((17488.68778 663.65102) (17481.14819 667.42081)))
("SF_PLANTING" 0 ((17484.91516 874.81052) (17481.30147 852.18609) (17484.91109 833.33428) (17484.91109 682.50283)
(17481.14819 667.42081)))
("SF_PLANTING" 0 ((17484.91516 874.81052) (17515.08484 882.35294)))
("SF_PLANTING" 0 ((17484.91516 618.40215) (17484.92353 520.36199) (17488.84106 510.25464) (17677.22285 505.28484)
(17760.18100 514.70588)))
("SF_PLANTING" 0 ((17484.91516 618.40215) (17488.54005 629.71437) (17488.68778 663.65102)))
("SF_PLANTING" 0 ((17488.68778 1131.22172) (17486.80430 1148.19005)))
("SF_PLANTING" 0 ((17500.00000 1153.84615) (17486.80430 1148.19005)))
("SF_PLANTING" 0 ((17511.31222 4027.14932) (17503.76425 4020.80554) (17488.68778 4019.60826)))
("SF_PLANTING" 0 ((17488.68778 1003.01753) (17511.31222 1004.07319) (17537.70928 1021.86934)))
("SF_PLANTING" 0 ((17488.68778 663.65102) (17514.93428 668.47715) (17530.31459 693.66176) (17544.19253 701.51210)
(17553.84627 723.98190) (17564.10068 735.29412)))
("SF_PLANTING" 0 ((17492.46041 1202.86482) (17502.56708 1191.55260) (17503.77262 1180.24038)))
("SF_PLANTING" 0 ((17496.22738 1052.03620) (17537.70928 1055.80600)))
("SF_PLANTING" 0 ((17530.16403 1108.59729) (17521.42025 1131.22172) (17500.00000 1153.84615)))
("SF_PLANTING" 0 ((17500.00000 1153.84615) (17503.77262 1180.24038)))
("SF_ARCHITECTURE" 0 ((17503.77262 5199.84876) (17503.77670 5011.31222) (17507.53552 4992.45894) (17507.53959
4155.35486)))
("SF_ARCHITECTURE" 0 ((17560.33179 5203.61991) (17518.85181 5203.47183) (17503.77262 5199.84876)))
("SF_ARCHITECTURE" 0 ((17503.77262 2356.71165) (17503.77670 1564.85577) (17507.53959 1542.23133) (17507.53552
1414.02715) (17503.91900 1398.94514) (17503.77670 1357.46606) (17510.10113 1338.61143) (17500.01244 1312.21719)
(17504.96844 1282.05792) (17511.31222 1274.51075)))
("SF_ARCHITECTURE" 0 ((17503.77262 2356.71165) (17522.62443 2360.48292) (17545.24197 2360.33518) (17552.78846
2356.71165)))
("SF_PLANTING" 0 ((17549.02149 1165.15837) (17503.77262 1180.24038)))
("SF_PLANTING" 0 ((17507.53959 4155.35486) (17530.15995 4155.20645) (17537.70928 4151.58371)))
("SF_PLANTING" 0 ((17515.08484 4113.87590) (17507.53959 4155.35486)))
("SF_PLANTING" 0 ((17533.93665 4038.46154) (17525.33925 4072.39819) (17511.31222 4091.25147)))
("SF_PLANTING" 0 ((17511.31222 4027.14932) (17499.10656 4042.23269) (17496.22738 4057.31482) (17497.43292 4083.56233)
(17511.31222 4091.25147)))
("SF_PLANTING" 0 ((17515.08484 4113.87590) (17511.31222 4091.25147)))
("SF_PLANTING" 0 ((17522.62443 4027.14932) (17511.31222 4027.14932)))
("SF_PLANTING" 0 ((17511.31222 3804.67613) (17530.16403 3804.67613)))
("SF_PLANTING" 0 ((17511.31222 1274.51075) (17541.47624 1274.51075)))
("SF_PLANTING" 0 ((17530.16403 4117.64706) (17515.08484 4113.87590)))
("SF_PLANTING" 0 ((17515.08484 882.35294) (17545.09559 855.81029) (17551.74174 840.87387) (17556.41335 795.62500)
(17549.02149 769.23077)))
("SF_PLANTING" 0 ((17526.39706 946.45645) (17515.23122 901.20758) (17515.08484 882.35294)))
("SF_PLANTING" 0 ((17549.02149 3996.98382) (17537.85566 4004.53111) (17522.62443 4027.14932)))
("SF_PLANTING" 0 ((17533.93665 4038.46154) (17522.62443 4027.14932)))
("SF_PLANTING" 0 ((17522.62443 803.16742) (17526.39706 833.33428)))
("SF_PLANTING" 0 ((17526.39706 946.45645) (17535.13247 969.08088) (17586.87568 1036.80577) (17601.80995 1047.07534)
(17624.43439 1052.03620)))
("SF_PLANTING" 0 ((17526.39706 769.23077) (17526.39706 746.60633)))
("SF_PLANTING" 0 ((17541.47624 599.54751) (17534.07749 597.12952) (17527.45204 607.08993) (17523.82025 625.93688)
(17526.39706 633.48416)))
("SF_PLANTING" 0 ((17598.03733 4095.02262) (17552.78846 4109.95102) (17537.71335 4111.30328) (17530.16403 4117.64706)))
("SF_PLANTING" 0 ((17530.16403 4117.64706) (17537.70928 4151.58371)))
("SF_PLANTING" 0 ((17560.33371 3804.67613) (17549.02149 3800.91810) (17530.16403 3804.67613)))
("SF_PLANTING" 0 ((17530.16403 3804.67613) (17535.13247 3823.52941) (17541.48462 3830.92262) (17579.18552 3852.63948)
(17612.97443 3852.49106) (17620.66176 3834.84163)))
("SF_PLANTING" 0 ((17530.16403 1108.59729) (17560.33371 1110.48360)))
("SF_PLANTING" 0 ((17533.93665 4038.46154) (17567.86640 4033.49310) (17574.35792 4027.14310) (17582.95814 4004.52489)))
("SF_PLANTING" 0 ((17556.56109 558.06844) (17545.25577 555.65192) (17533.93665 573.15328)))
("SF_PLANTING" 0 ((17549.02149 4151.58371) (17537.70928 4151.58371)))
("SF_PLANTING" 0 ((17537.70928 1055.80600) (17541.47624 1040.72398)))
("SF_PLANTING" 0 ((17560.33371 1110.48360) (17555.51165 1078.43043) (17547.96369 1063.35532) (17537.70928 1055.80600)))
("SF_PLANTING" 0 ((17552.78846 1251.88631) (17542.68179 1263.19853) (17541.47624 1274.51075)))
("SF_PLANTING" 0 ((17560.33371 1312.21719) (17541.47624 1274.51075)))
("SF_PLANTING" 0 ((17560.33371 4140.27149) (17549.02149 4151.58371)))
("SF_ARCHITECTURE" 0 ((17560.33179 5203.61991) (17560.33179 5188.53654) (17556.55419 4166.66708) (17549.02149
4151.58371)))
("SF_PLANTING" 0 ((17549.02149 3996.98382) (17564.10068 3947.96380)))
("SF_PLANTING" 0 ((17549.02149 3996.98382) (17582.95814 4004.52489)))
("SF_PLANTING" 0 ((17560.33371 1110.48360) (17549.02149 1165.15837)))
("SF_PLANTING" 0 ((17549.02149 1165.15837) (17556.56109 1191.55260)))
("SF_ARCHITECTURE" 0 ((17560.33371 1312.21719) (17556.56799 1323.52941) (17556.55419 2326.54627) (17552.78846
2356.71165)))
("SF_ARCHITECTURE" 0 ((17613.12217 2352.94118) (17594.27036 2360.33439) (17552.78846 2356.71165)))
("SF_PLANTING" 0 ((17552.78846 1251.88631) (17556.56109 1191.55260)))
("SF_PLANTING" 0 ((17552.78846 1251.88631) (17571.64593 1259.42590)))
("SF_PLANTING" 0 ((17564.10068 629.71437) (17552.94457 641.02658) (17549.03111 663.65102) (17552.78846 674.96324)))
("SF_PLANTING" 0 ((17556.56109 1191.55260) (17609.34955 1187.78281)))
("SF_PLANTING" 0 ((17556.56109 893.66516) (17564.10068 946.45645)))
("SF_ARCHITECTURE" 0 ((17560.33179 5203.61991) (17598.03326 5203.47183) (17605.58258 5199.84876)))
("SF_PLANTING" 0 ((17560.33371 3740.57274) (17561.53643 3717.94898) (17571.64593 3706.63609)))
("SF_PLANTING" 0 ((17560.33371 3740.57274) (17616.89480 3748.11505) (17628.05090 3746.91029) (17631.82070 3740.56652)
(17635.74661 3684.01165) (17631.98235 3657.61731) (17631.98235 3529.41176) (17635.45113 3514.32907) (17632.12319
3503.01686) (17633.64762 3469.08020) (17620.66176 3438.91403)))
("SF_PLANTING" 0 ((17560.33371 1312.21719) (17609.34955 1315.98699)))
("SF_PLANTING" 0 ((17560.33371 1110.48360) (17616.89480 1131.22172)))
("SF_PLANTING" 0 ((17613.12217 3906.48609) (17604.38394 3925.33937) (17586.72511 3944.03869) (17564.10068 3947.96380)))
("SF_PLANTING" 0 ((17571.64593 3902.71493) (17564.25679 3917.79830) (17564.10068 3947.96380)))
("SF_PLANTING" 0 ((17613.12217 3906.48609) (17605.57421 3902.86301) (17571.64593 3902.71493)))
("SF_PLANTING" 0 ((17609.34955 3823.52941) (17579.18552 3819.75826)))
("SF_PLANTING" 0 ((17601.80995 4000.75373) (17582.95814 4004.52489)))
("SF_PLANTING" 0 ((17598.03733 4095.02262) (17602.85939 4064.85713) (17619.61505 4030.92048) (17624.43439 4004.52489)))
("SF_PLANTING" 0 ((17598.03733 4095.02262) (17609.34955 4098.79378)))
("SF_PLANTING" 0 ((17639.51923 3978.12930) (17628.20701 3970.74287) (17605.58665 3971.79276) (17598.19344 3981.90045)
(17601.80995 4000.75373)))
("SF_PLANTING" 0 ((17624.43439 4004.52489) (17601.80995 4000.75373)))
("SF_PLANTING" 0 ((17613.12217 3797.13382) (17601.80995 3782.05170)))
("SF_PLANTING" 0 ((17601.80995 3431.37229) (17620.66176 3438.91403)))
("SF_PLANTING" 0 ((17628.20701 927.60181) (17601.80995 927.60181)))
("SF_PLANTING" 0 ((17601.80995 927.60181) (17598.04570 904.97738) (17602.86629 889.90023) (17639.51923 863.49830)))
("SF_PLANTING" 0 ((17624.43439 1052.03620) (17623.37805 1033.18156) (17606.62930 1003.01753) (17598.18654 972.85068)
(17601.80995 927.60181)))
("SF_ARCHITECTURE" 0 ((17628.20701 5199.84876) (17605.58258 5199.84876)))
("SF_ARCHITECTURE" 0 ((17613.12217 5147.05882) (17601.96324 5158.37104) (17601.95769 5192.30147) (17605.58258
5199.84876)))
("SF_PLANTING" 0 ((17624.43439 829.56165) (17605.58258 833.33428)))
("SF_ARCHITECTURE" 0 ((17609.34955 5663.65011) (17662.14367 5663.65011) (17680.99548 5663.65011) (17873.30317
5663.65011) (17895.92760 5663.65011) (17922.32466 5663.65011) (17963.80090 5663.65011)))
("SF_ARCHITECTURE" 0 ((17613.12217 5147.05882) (17613.11527 4626.69683) (17609.34955 4604.07240) (17613.12217
4539.97025) (17609.35792 4434.38914) (17613.11527 4381.59921) (17609.35792 4362.74468) (17609.34955 4098.79378)))
("SF_PLANTING" 0 ((17662.14367 4102.56369) (17609.34955 4098.79378)))
("SF_PLANTING" 0 ((17609.34955 3823.52941) (17613.12217 3797.13382)))
("SF_PLANTING" 0 ((17609.34955 3823.52941) (17620.66176 3834.84163)))
("SF_PLANTING" 0 ((17613.12217 1312.21719) (17613.12217 1315.98699) (17609.34955 1315.98699)))
("SF_PLANTING" 0 ((17609.34955 1315.98699) (17613.12217 1312.21719)))
("SF_ARCHITECTURE" 0 ((17613.12217 2352.94118) (17613.11527 1406.48473) (17609.49876 1391.40271) (17609.34955
1315.98699)))
("SF_PLANTING" 0 ((17616.89480 1165.15837) (17610.54819 1172.70566) (17609.34955 1187.78281)))
("SF_PLANTING" 0 ((17613.12217 1217.94966) (17609.49876 1210.40034) (17609.34955 1187.78281)))
("SF_ARCHITECTURE" 0 ((17613.12217 5147.05882) (17623.23857 5158.37104) (17627.15611 5169.68326) (17628.20701
5199.84876)))
("SF_PLANTING" 0 ((17613.12217 3906.48609) (17620.66176 3906.48609)))
("SF_PLANTING" 0 ((17652.71493 3829.18552) (17650.60079 3819.82590) (17639.51923 3808.59446) (17613.12217 3797.13382)))
("SF_ARCHITECTURE" 0 ((17665.91063 2315.23405) (17661.98756 2352.93428) (17658.21776 2359.27873) (17628.20701
2360.32828) (17613.12217 2352.94118)))
("SF_PLANTING" 0 ((17613.12217 1312.21719) (17665.91063 1312.21719)))
("SF_PLANTING" 0 ((17613.12217 1217.94966) (17609.34955 1255.65611) (17609.49876 1300.90498) (17613.12217 1312.21719)))
("SF_PLANTING" 0 ((17613.12217 1217.94966) (17624.43439 1214.32545) (17669.68326 1214.17704)))
("SF_PLANTING" 0 ((17613.12217 573.15328) (17635.74661 576.92308)))
("SF_PLANTING" 0 ((17616.89480 3246.60633) (17620.66176 3227.75238) (17616.89887 3205.12794) (17616.89887 3073.15260)
(17620.66176 3061.84038)))
("SF_PLANTING" 0 ((17616.89480 1165.15837) (17654.59842 1161.38857)))
("SF_PLANTING" 0 ((17616.89480 1131.22172) (17616.89480 1165.15837)))
("SF_PLANTING" 0 ((17665.91063 1119.90950) (17628.20701 1123.83462) (17616.89480 1131.22172)))
("SF_PLANTING" 0 ((17647.05882 3895.17387) (17635.74661 3896.22998) (17620.66176 3906.48609)))
("SF_PLANTING" 0 ((17665.91063 3955.50486) (17647.20656 3940.42274) (17620.66176 3906.48609)))
("SF_PLANTING" 0 ((17652.71493 3829.18552) (17620.66176 3834.84163)))
("SF_PLANTING" 0 ((17635.74661 3427.60181) (17620.66176 3438.91403)))
("SF_PLANTING" 0 ((17624.43439 4004.52489) (17639.51923 3978.12930)))
("SF_PLANTING" 0 ((17665.91063 1074.66063) (17639.51923 1069.83371) (17624.43439 1052.03620)))
("SF_PLANTING" 0 ((17624.43439 829.56165) (17635.74661 806.93722)))
("SF_PLANTING" 0 ((17624.43439 829.56165) (17629.26199 848.41629) (17639.51923 863.49830)))
("SF_PLANTING" 0 ((17624.43439 629.71437) (17639.51923 633.48416)))
("SF_ARCHITECTURE" 0 ((17669.68326 5139.51776) (17662.29695 5150.82998) (17664.70792 5192.30769) (17650.83145
5203.46527) (17628.20701 5199.84876)))
("SF_PLANTING" 0 ((17677.22285 920.05939) (17654.59842 920.20781) (17628.20701 927.60181)))
("SF_PLANTING" 0 ((17658.37104 957.76867) (17643.43676 950.07783) (17628.20701 927.60181)))
("SF_PLANTING" 0 ((17631.97398 739.06391) (17632.12319 686.27545) (17643.28620 663.65102)))
("SF_PLANTING" 0 ((17631.97398 739.06391) (17617.04808 743.89219) (17613.27545 754.14876) (17635.74661 806.93722)))
("SF_PLANTING" 0 ((17631.97398 739.06391) (17654.45204 750.52455) (17668.33133 769.23077) (17658.37104 806.93722)))
("SF_PLANTING" 0 ((17635.74661 3314.47964) (17635.59887 3359.72851) (17632.13009 3371.04072) (17635.74661 3427.60181)))
("SF_PLANTING" 0 ((17635.74661 3427.60181) (17647.05882 3435.14355)))
("SF_PLANTING" 0 ((17635.74661 3314.47964) (17647.05882 3310.85690) (17692.30769 3310.55452) (17707.39253 3299.39695)))
("SF_PLANTING" 0 ((17635.74661 3314.47964) (17620.97251 3295.63258) (17624.58767 3289.14106) (17635.74661 3284.46199)
(17692.30769 3288.23937) (17707.39253 3299.39695)))
("SF_PLANTING" 0 ((17658.37104 806.93722) (17635.74661 806.93722)))
("SF_PLANTING" 0 ((17662.14367 3978.12930) (17639.51923 3978.12930)))
("SF_PLANTING" 0 ((17679.11199 865.38462) (17639.51923 863.49830)))
("SF_PLANTING" 0 ((17675.33937 667.42081) (17677.00328 659.87353) (17669.52998 630.91776) (17639.51923 633.48416)))
("SF_PLANTING" 0 ((17643.28620 663.65102) (17639.66561 656.10170) (17639.51923 633.48416)))
("SF_PLANTING" 0 ((17675.33937 667.42081) (17650.83552 667.27308) (17643.28620 663.65102)))
("SF_PLANTING" 0 ((17647.05882 3895.17387) (17650.68224 3887.62534) (17652.71493 3829.18552)))
("SF_PLANTING" 0 ((17647.05882 3895.17387) (17673.29977 3910.40441) (17688.53507 3947.96380)))
("SF_PLANTING" 0 ((17745.09615 3910.25600) (17718.85113 3891.40271) (17697.13529 3865.00713) (17688.38179 3843.43937)
(17652.71493 3829.18552)))
("SF_PLANTING" 0 ((17658.37104 957.76867) (17668.48744 950.21934) (17677.22285 927.60181)))
("SF_PLANTING" 0 ((17665.91063 1074.66063) (17665.76425 1044.49378) (17658.51878 1018.09955) (17658.37104 957.76867)))
("SF_PLANTING" 0 ((17658.37104 806.93722) (17672.25034 818.25701) (17679.11199 865.38462)))
("SF_PLANTING" 0 ((17662.14367 3978.12930) (17672.25034 3989.44219) (17673.45588 4000.75373) (17662.14367 4102.56369)))
("SF_ARCHITECTURE" 0 ((17662.14367 4102.56369) (17669.68326 4147.81256) (17669.68326 4358.97477) (17669.68326
4381.59921) (17669.68326 4883.10667) (17669.68326 4901.96120) (17669.68326 5018.85328) (17669.68326 5052.78993)
(17669.68326 5071.64446)))
("SF_PLANTING" 0 ((17662.14367 3978.12930) (17665.91063 3955.50486)))
("SF_PLANTING" 0 ((17662.14367 3699.09502) (17662.14367 3691.55396)))
("SF_PLANTING" 0 ((17665.91063 3955.50486) (17688.53507 3947.96380)))
("SF_ARCHITECTURE" 0 ((17665.91063 2315.23405) (17666.05984 2251.13812) (17669.68326 2243.58948)))
("SF_ARCHITECTURE" 0 ((17665.91063 2315.23405) (17688.53507 2323.83145) (17730.01697 2360.33439) (17794.11765
2404.67534) (17880.84276 2449.93111) (17937.40385 2472.40713) (18016.58937 2495.17930) (18065.61086 2503.62274)
(18092.00792 2503.77048)))
("SF_PLANTING" 0 ((17665.91063 1304.67477) (17665.91063 1312.21719)))
("SF_ARCHITECTURE" 0 ((17669.68326 2243.58948) (17665.91900 2213.42410) (17665.91063 1312.21719)))
("SF_PLANTING" 0 ((17696.08032 1289.59276) (17692.15441 1303.47138) (17665.91063 1304.67477)))
("SF_PLANTING" 0 ((17665.91063 1304.67477) (17666.05984 1282.05034) (17670.87907 1263.20339) (17677.22285 1255.65611)))
("SF_PLANTING" 0 ((17665.91063 1202.86482) (17669.68326 1214.17704)))
("SF_PLANTING" 0 ((17665.91063 1074.66063) (17665.91063 1119.90950)))
("SF_PLANTING" 0 ((17680.99548 1127.45192) (17665.91063 1119.90950)))
("SF_PLANTING" 0 ((17665.91063 1074.66063) (17699.84729 1069.69219) (17718.55419 1058.52149) (17726.24434 1044.49378)))
("SF_ARCHITECTURE" 0 ((17669.68326 5139.51776) (17662.14367 5090.49774) (17663.33948 5079.19174) (17669.68326
5071.64446)))
("SF_ARCHITECTURE" 0 ((18092.00792 5324.28314) (18061.83824 5324.13529) (18005.27715 5311.92138) (17929.86425
5289.29106) (17873.30317 5266.67285) (17801.65724 5228.96505) (17722.47172 5176.17477) (17688.53507 5148.11550)
(17669.68326 5139.51776)))
("SF_ARCHITECTURE" 0 ((18099.54751 5267.72206) (18076.92308 5267.57421) (18012.82240 5255.36063) (17941.17647
5232.72998) (17888.38801 5210.11176) (17797.89027 5161.08586) (17699.84729 5084.00588) (17669.68326 5071.64446)))
("SF_PLANTING" 0 ((17669.68326 3585.97285) (17677.23122 3596.08710) (17711.15950 3604.82681)))
("SF_PLANTING" 0 ((17669.68326 3533.18224) (17670.73959 3518.09955) (17677.22285 3506.78733)))
("SF_ARCHITECTURE" 0 ((17669.68326 2243.58948) (17695.92975 2255.05023) (17707.39661 2269.83665) (17782.80543
2333.03778) (17835.59389 2366.97443) (17888.38801 2393.36934) (17975.11312 2427.29977) (18069.38348 2447.06165)
(18099.54751 2447.20939)))
("SF_PLANTING" 0 ((17669.68326 1214.17704) (17677.07647 1229.26188) (17677.22285 1255.65611)))
("SF_PLANTING" 0 ((17673.45588 3736.80283) (17671.03518 3763.19717) (17692.30769 3785.67376) (17707.39253 3793.36391)))
("SF_PLANTING" 0 ((17673.45588 3333.33360) (17677.21878 3367.27025) (17677.22285 3476.62115)))
("SF_PLANTING" 0 ((17675.33937 667.42081) (17673.60226 682.50283) (17682.05181 701.35747) (17692.30769 711.61335)
(17711.15950 720.21210)))
("SF_PLANTING" 0 ((17675.33937 667.42081) (17703.61991 676.16663) (17733.78394 705.12726)))
("SF_PLANTING" 0 ((17696.08032 1266.96833) (17692.15441 1260.47613) (17677.22285 1255.65611)))
("SF_PLANTING" 0 ((17677.22285 920.05939) (17677.22285 927.60181)))
("SF_PLANTING" 0 ((17730.01697 931.37161) (17688.53507 931.22455) (17677.22285 927.60181)))
("SF_PLANTING" 0 ((17677.22285 920.05939) (17679.11199 865.38462)))
("SF_PLANTING" 0 ((17679.11199 865.38462) (17714.93213 867.27093)))
("SF_PLANTING" 0 ((17730.01697 1116.13971) (17714.93213 1112.51550) (17696.08032 1117.19536) (17680.99548 1127.45192)))
("SF_PLANTING" 0 ((17680.99548 1127.45192) (17688.68563 1141.47760) (17714.93213 1150.07636)))
("SF_PLANTING" 0 ((17688.53507 3947.96380) (17737.55656 3944.04480) (17779.03281 3932.88733) (17794.11765 3933.93710)
(17812.96946 3944.19265)))
("SF_PLANTING" 0 ((17758.29751 624.05826) (17726.25124 625.78846) (17719.90747 622.01731) (17713.72794 580.69287)
(17693.51188 561.83348) (17692.30769 550.52885)))
("SF_PLANTING" 0 ((17696.08032 3653.84615) (17722.47172 3657.61731)))
("SF_PLANTING" 0 ((17737.55656 3699.09502) (17718.70475 3697.89740) (17703.61991 3687.78281)))
("SF_PLANTING" 0 ((17714.93213 4147.81256) (17711.15950 4151.58371) (17707.39253 4147.81256)))
("SF_PLANTING" 0 ((17707.39253 4072.39819) (17707.24333 4057.31482) (17697.43213 4023.37817) (17722.47172 3998.03993)
(17745.09615 3993.21267)))
("SF_PLANTING" 0 ((17707.39253 3808.44604) (17707.39253 3793.36391)))
("SF_PLANTING" 0 ((17752.64140 3755.65611) (17730.02104 3767.11640) (17714.79129 3789.43812) (17707.39253 3793.36391)))
("SF_PLANTING" 0 ((17771.49321 3299.39695) (17707.39253 3299.39695)))
("SF_PLANTING" 0 ((17722.47172 1331.07183) (17707.39253 1327.29921)))
("SF_PLANTING" 0 ((17707.39253 731.52432) (17711.15950 720.21210)))
("SF_PLANTING" 0 ((17718.70475 3589.74333) (17711.15950 3597.28507) (17711.15950 3604.82681)))
("SF_PLANTING" 0 ((17741.32919 3631.22172) (17730.01697 3627.29661) (17711.15950 3604.82681)))
("SF_PLANTING" 0 ((17718.70475 980.39310) (17718.54864 1010.55713) (17711.15950 1021.86934)))
("SF_PLANTING" 0 ((17718.70475 980.39310) (17703.77319 985.21923) (17696.23360 1003.01753) (17700.00339 1014.18133)
(17711.15950 1021.86934)))
("SF_PLANTING" 0 ((17711.15950 1021.86934) (17726.24434 1044.49378)))
("SF_PLANTING" 0 ((17733.78394 705.12726) (17718.70882 719.00724) (17711.15950 720.21210)))
("SF_PLANTING" 0 ((17730.01697 1116.13971) (17725.05407 1134.99152) (17714.93213 1150.07636)))
("SF_PLANTING" 0 ((17737.55656 1172.70079) (17716.13631 1157.46889) (17714.93213 1150.07636)))
("SF_PLANTING" 0 ((17730.01697 844.64649) (17714.93213 867.27093)))
("SF_PLANTING" 0 ((17737.55656 889.89536) (17722.48009 878.58314) (17714.93213 867.27093)))
("SF_PLANTING" 0 ((17718.70475 3589.74333) (17718.70475 3574.66063)))
("SF_PLANTING" 0 ((17718.70475 3589.74333) (17736.50023 3601.06244) (17741.17998 3612.36776) (17741.32919 3631.22172)))
("SF_PLANTING" 0 ((17718.70475 980.39310) (17752.64140 953.99604)))
("SF_PLANTING" 0 ((17730.01697 478.88292) (17718.70475 456.25848)))
("SF_PLANTING" 0 ((17722.47172 4117.64706) (17730.17025 4083.71663) (17745.09615 4073.45486) (17760.18100 4072.39819)))
("SF_PLANTING" 0 ((17722.47172 3657.61731) (17741.32919 3638.76278)))
("SF_PLANTING" 0 ((17750.75226 3689.66776) (17722.47172 3657.61731)))
("SF_PLANTING" 0 ((17722.47172 3363.49898) (17730.01697 3355.95803)))
("SF_PLANTING" 0 ((17726.24434 3842.38269) (17741.32919 3842.38269)))
("SF_PLANTING" 0 ((17726.24434 1289.59276) (17730.01697 1300.90498)))
("SF_PLANTING" 0 ((17756.40837 1044.49378) (17726.24434 1044.49378)))
("SF_PLANTING" 0 ((17730.01697 1270.73812) (17737.55656 1259.42590)))
("SF_PLANTING" 0 ((17730.01697 1116.13971) (17760.18100 1116.29299) (17775.26584 1127.45192)))
("SF_PLANTING" 0 ((17737.55656 889.89536) (17730.01697 931.37161)))
("SF_PLANTING" 0 ((17730.01697 931.37161) (17752.64140 953.99604)))
("SF_PLANTING" 0 ((17730.01697 844.64649) (17730.01697 814.47964)))
("SF_PLANTING" 0 ((17730.01697 844.64649) (17771.49321 844.79355) (17782.80543 848.41629)))
("SF_PLANTING" 0 ((17767.72059 791.85520) (17763.79751 799.25532) (17748.86878 809.65894) (17730.01697 814.47964)))
("SF_PLANTING" 0 ((17756.40837 765.46097) (17722.48009 763.94265) (17716.12794 769.24321) (17712.36505 791.85520)
(17730.01697 814.47964)))
("SF_PLANTING" 0 ((17730.01697 384.61538) (17741.32919 395.92760)))
("SF_PLANTING" 0 ((17733.78394 4042.23269) (17733.78394 4034.69038)))
("SF_PLANTING" 0 ((17745.09615 705.12726) (17733.78394 705.12726)))
("SF_PLANTING" 0 ((17750.75226 3689.66776) (17737.55656 3699.09502)))
("SF_PLANTING" 0 ((17737.55656 3699.09502) (17738.61290 3721.71946) (17745.23982 3732.87704) (17752.64140 3736.80283)))
("SF_PLANTING" 0 ((17752.64140 1259.42590) (17737.55656 1259.42590)))
("SF_PLANTING" 0 ((17737.55656 1172.70079) (17731.21278 1180.24796) (17726.53982 1210.40724) (17730.17025 1248.11369)
(17737.55656 1259.42590)))
("SF_PLANTING" 0 ((17737.55656 1172.70079) (17756.40837 1172.70079)))
("SF_PLANTING" 0 ((17737.55656 889.89536) (17782.80543 886.12274)))
("SF_PLANTING" 0 ((17752.64140 3755.65611) (17760.02771 3770.73948) (17756.26199 3808.44604) (17741.32919 3842.38269)))
("SF_PLANTING" 0 ((17741.32919 3842.38269) (17746.15396 3857.31799) (17763.95362 3871.35158) (17790.34502 3876.31934)))
("SF_PLANTING" 0 ((17748.86878 3638.76278) (17741.32919 3638.76278)))
("SF_PLANTING" 0 ((17741.32919 3631.22172) (17741.32919 3638.76278)))
("SF_PLANTING" 0 ((17775.26584 3981.90045) (17749.02206 3986.86233) (17745.09615 3993.21267)))
("SF_PLANTING" 0 ((17763.95362 4012.06595) (17752.78778 4007.23937) (17745.09615 3993.21267)))
("SF_PLANTING" 0 ((17745.09615 705.12726) (17753.69638 686.27545) (17767.72059 671.19061)))
("SF_PLANTING" 0 ((17745.09615 705.12726) (17760.18100 739.06391)))
("SF_PLANTING" 0 ((17748.86878 3638.76278) (17790.34502 3616.13903)))
("SF_PLANTING" 0 ((17748.86878 3638.76278) (17763.95362 3672.69943)))
("SF_PLANTING" 0 ((17750.75226 3689.66776) (17763.95362 3672.69943)))
("SF_PLANTING" 0 ((17750.75226 3689.66776) (17767.56731 3710.40724) (17766.51787 3721.71946) (17752.64140 3736.80283)))
("SF_PLANTING" 0 ((17752.64140 3748.11505) (17752.64140 3755.65611)))
("SF_PLANTING" 0 ((17752.64140 3748.11505) (17794.11765 3748.11505)))
("SF_PLANTING" 0 ((17752.64140 3748.11505) (17752.64140 3736.80283)))
("SF_PLANTING" 0 ((17756.40837 1172.70079) (17763.79751 1191.55260) (17760.32873 1202.86482) (17760.02771 1248.11369)
(17752.64140 1259.42590)))
("SF_PLANTING" 0 ((17763.95362 1285.82296) (17752.64140 1259.42590)))
("SF_PLANTING" 0 ((17752.64140 953.99604) (17763.94525 954.21912) (17771.49321 959.65215)))
("SF_PLANTING" 0 ((17756.40837 1172.70079) (17761.23043 1150.07636) (17775.26584 1127.45192)))
("SF_PLANTING" 0 ((17771.49321 959.65215) (17764.10000 999.24491) (17763.79751 1029.41176) (17756.40837 1044.49378)))
("SF_PLANTING" 0 ((17786.57805 1059.57862) (17767.72059 1054.60260) (17756.40837 1044.49378)))
("SF_PLANTING" 0 ((17756.40837 765.46097) (17760.18100 739.06391)))
("SF_PLANTING" 0 ((17756.40837 765.46097) (17767.72059 791.85520)))
("SF_PLANTING" 0 ((17758.29751 624.05826) (17797.89027 614.62952)))
("SF_PLANTING" 0 ((17758.29751 624.05826) (17760.17410 561.84106) (17756.42217 542.98643) (17760.18100 514.70588)))
("SF_PLANTING" 0 ((17758.29751 624.05826) (17767.72059 671.19061)))
("SF_PLANTING" 0 ((17760.18100 4072.39819) (17766.51787 4061.08597) (17763.95362 4012.06595)))
("SF_PLANTING" 0 ((17763.95362 4102.56369) (17760.18100 4072.39819)))
("SF_PLANTING" 0 ((17801.65724 735.29412) (17760.18100 739.06391)))
("SF_PLANTING" 0 ((17760.18100 514.70588) (17775.26584 509.19751) (17828.05430 509.04977)))
("SF_PLANTING" 0 ((17760.18100 478.88292) (17760.18100 514.70588)))
("SF_PLANTING" 0 ((17767.72059 392.15781) (17760.32873 414.78224) (17760.18100 441.17647)))
("SF_ARCHITECTURE" 0 ((17763.95362 4102.56369) (17760.18790 4136.50034) (17760.18100 4981.14672) (17765.15633
5007.39321) (17843.13914 5051.59921) (17967.57353 5100.75396) (18054.29864 5124.28631) (18144.79638 5135.74038)
(18269.23077 5128.05713) (18386.12557 5100.75328) (18457.76584 5074.36516) (18559.57579 5019.76188) (18582.20023
5011.31222)))
("SF_PLANTING" 0 ((17763.95362 4102.56369) (17786.57805 4111.16210) (17805.28213 4126.23857) (17812.96946 4144.04265)))
("SF_PLANTING" 0 ((17775.26584 3981.90045) (17774.06029 4004.51867) (17763.95362 4012.06595)))
("SF_PLANTING" 0 ((17805.42986 3672.69943) (17763.95362 3672.69943)))
("SF_ARCHITECTURE" 0 ((18578.43326 1210.40724) (18585.96595 1225.48925) (18585.97285 1708.14480) (18585.97285
1730.76923) (18585.97285 1813.72455) (18585.97285 1832.57919) (18580.99751 2179.33891) (18533.18439 2212.37455)
(18435.14140 2257.62342) (18322.01923 2291.55939) (18242.83371 2303.77410) (18110.85973 2303.77410) (18031.67421
2292.46188) (17982.65271 2280.24095) (17884.61538 2246.31120) (17775.26584 2193.51380) (17765.14943 2183.25792)
(17763.95170 2160.63348) (17763.95170 2104.07240) (17763.95170 2085.21844) (17763.95170 2051.28179) (17760.18790
1297.13518) (17763.95362 1285.82296)))
("SF_PLANTING" 0 ((17763.95362 1285.82296) (17782.80543 1290.64910) (17812.96946 1315.98699)))
("SF_PLANTING" 0 ((17767.72059 312.97229) (17770.29457 328.05430) (17763.95362 346.90894)))
("SF_PLANTING" 0 ((17797.89027 793.74152) (17767.72059 791.85520)))
("SF_PLANTING" 0 ((17790.34502 671.19061) (17767.72059 671.19061)))
("SF_PLANTING" 0 ((17790.34502 3472.85068) (17768.77839 3435.14355) (17771.49321 3408.74785)))
("SF_PLANTING" 0 ((17771.49321 3299.39695) (17775.41912 3293.05317) (17786.57805 3291.85520) (17801.65317 3293.05317)
(17809.20249 3299.39695)))
("SF_PLANTING" 0 ((17771.49321 3299.39695) (17779.04118 3305.74005) (17790.34502 3306.93790) (17801.65317 3305.74005)
(17809.20249 3299.39695)))
("SF_PLANTING" 0 ((17771.49321 959.65215) (17786.57805 923.83201)))
("SF_PLANTING" 0 ((17771.49321 959.65215) (17786.57805 968.92557) (17812.96946 969.08088)))
("SF_PLANTING" 0 ((17814.85860 3955.50486) (17775.26584 3981.90045)))
("SF_PLANTING" 0 ((17775.26584 1127.45192) (17790.34502 1127.45192)))
("SF_PLANTING" 0 ((17782.80543 874.81052) (17782.80543 886.12274)))
("SF_PLANTING" 0 ((17786.57805 923.83201) (17782.95317 919.90611) (17782.80543 886.12274)))
("SF_PLANTING" 0 ((17809.20249 871.04072) (17782.80543 874.81052)))
("SF_PLANTING" 0 ((17782.80543 874.81052) (17782.80543 848.41629)))
("SF_PLANTING" 0 ((17797.89027 837.10407) (17786.73133 841.92410) (17782.80543 848.41629)))
("SF_PLANTING" 0 ((17786.57805 1059.57862) (17843.13914 1014.32975)))
("SF_PLANTING" 0 ((17794.11765 1104.82749) (17786.72443 1089.74265) (17786.57805 1059.57862)))
("SF_PLANTING" 0 ((17816.74208 923.83201) (17786.57805 923.83201)))
("SF_PLANTING" 0 ((17816.74208 3808.44604) (17806.48620 3815.99457) (17791.40283 3842.38269) (17790.34502 3876.31934)))
("SF_PLANTING" 0 ((17820.51471 3891.40271) (17790.34502 3876.31934)))
("SF_PLANTING" 0 ((17790.34502 3695.32387) (17805.42986 3695.32387)))
("SF_PLANTING" 0 ((17790.34502 3642.53394) (17790.34502 3616.13903)))
("SF_PLANTING" 0 ((17831.82692 3653.84615) (17826.99796 3634.99287) (17816.59434 3616.28676) (17801.65724 3608.75192)
(17794.27093 3609.79525) (17790.34502 3616.13903)))
("SF_PLANTING" 0 ((17801.65724 3510.55781) (17791.54502 3495.47511) (17790.34502 3472.85068)))
("SF_PLANTING" 0 ((17790.34502 3472.85068) (17828.05430 3474.05486) (17839.36652 3487.93337)))
("SF_PLANTING" 0 ((17794.11765 1104.82749) (17790.34502 1127.45192)))
("SF_PLANTING" 0 ((17809.20249 1165.15837) (17802.55351 1142.53394) (17790.34502 1127.45192)))
("SF_PLANTING" 0 ((17790.34502 671.19061) (17796.69163 663.64344) (17801.65724 641.02658)))
("SF_PLANTING" 0 ((17790.34502 671.19061) (17801.65724 693.81505)))
("SF_PLANTING" 0 ((17794.11765 3748.11505) (17804.38043 3717.94830) (17805.42986 3702.86618)))
("SF_PLANTING" 0 ((17809.20249 3751.88495) (17797.89027 3751.88495) (17794.11765 3748.11505)))
("SF_PLANTING" 0 ((17794.11765 1104.82749) (17861.99095 1108.59729)))
("SF_PLANTING" 0 ((17797.89027 3540.72398) (17805.43676 3547.06776) (17828.05430 3552.03620)))
("SF_PLANTING" 0 ((17797.89027 837.10407) (17805.42986 837.10407)))
("SF_PLANTING" 0 ((17797.89027 837.10407) (17797.89027 793.74152)))
("SF_PLANTING" 0 ((17801.65724 735.29412) (17805.28213 750.37613) (17797.89027 793.74152)))
("SF_PLANTING" 0 ((17843.13914 795.62500) (17797.89027 793.74152)))
("SF_PLANTING" 0 ((17797.89027 599.54751) (17797.89027 614.62952)))
("SF_PLANTING" 0 ((17797.89027 614.62952) (17801.65724 641.02658)))
("SF_PLANTING" 0 ((17797.89027 599.54751) (17824.12839 591.85181) (17831.67771 573.15328) (17831.82692 558.06844)))
("SF_PLANTING" 0 ((17797.89027 599.54751) (17794.27093 580.69287) (17802.71505 561.99434) (17809.20656 558.22376)
(17831.82692 558.06844)))
("SF_PLANTING" 0 ((17797.89027 467.57070) (17794.26538 452.48869) (17801.65724 437.40667)))
("SF_PLANTING" 0 ((17801.65724 735.29412) (17805.42296 716.43948) (17801.65724 693.81505)))
("SF_PLANTING" 0 ((17801.65724 693.81505) (17809.20249 690.04525)))
("SF_PLANTING" 0 ((17831.82692 629.71437) (17816.74208 639.96946) (17801.65724 641.02658)))
("SF_PLANTING" 0 ((17839.36652 3702.86618) (17805.42986 3702.86618)))
("SF_PLANTING" 0 ((17805.42986 3695.32387) (17805.42986 3702.86618)))
("SF_PLANTING" 0 ((17805.42986 3672.69943) (17805.42986 3695.32387)))
("SF_PLANTING" 0 ((17805.42986 3672.69943) (17831.82692 3653.84615)))
("SF_PLANTING" 0 ((17843.13914 806.93722) (17841.93360 818.24943) (17835.58982 825.63722) (17812.97783 830.76029)
(17805.42986 837.10407)))
("SF_PLANTING" 0 ((17809.20249 871.04072) (17805.42986 837.10407)))
("SF_ARCHITECTURE" 0 ((17809.20249 4996.22885) (17798.19683 4981.14672) (17801.81335 4973.61131) (17812.96946
4966.06335)))
("SF_PLANTING" 0 ((17816.74208 3753.77115) (17812.96946 3744.34389) (17809.20249 3751.88495)))
("SF_PLANTING" 0 ((17816.74208 3753.77115) (17809.20249 3751.88495)))
("SF_PLANTING" 0 ((17809.20249 3367.27025) (17820.51471 3360.78484) (17835.59389 3359.72851)))
("SF_PLANTING" 0 ((17809.20249 3299.39695) (17850.67873 3306.93790) (17865.76357 3305.88156) (17877.07579 3299.39695)))
("SF_PLANTING" 0 ((17824.28167 1270.73812) (17810.25747 1244.34389) (17809.20249 1229.26188)))
("SF_PLANTING" 0 ((17809.20249 1165.15837) (17814.16810 1191.55260) (17914.62613 1319.75962) (17922.02217 1338.60656)
(17918.39876 1344.94898) (17907.23982 1346.00543) (17888.38801 1341.18541) (17843.13914 1317.03790) (17812.96946
1315.98699)))
("SF_PLANTING" 0 ((17809.20249 1165.15837) (17846.90611 1173.89106) (17907.23982 1209.35090) (17933.63688 1206.63744)))
("SF_PLANTING" 0 ((17809.20249 871.04072) (17846.90611 867.27093)))
("SF_ARCHITECTURE" 0 ((17812.96946 4144.04265) (17812.96946 4966.06335)))
("SF_ARCHITECTURE" 0 ((17937.40385 5041.47771) (17907.23982 5020.05113) (17854.45136 4995.17964) (17812.96946
4966.06335)))
("SF_PLANTING" 0 ((17926.09163 4177.97930) (17888.38801 4169.24627) (17846.90611 4148.86923) (17812.96946 4144.04265)))
("SF_PLANTING" 0 ((17812.96946 4038.46154) (17816.74208 4087.48156)))
("SF_PLANTING" 0 ((17820.51471 3891.40271) (17812.96946 3944.19265)))
("SF_PLANTING" 0 ((17814.85860 3955.50486) (17812.96946 3944.19265)))
("SF_ARCHITECTURE" 0 ((17820.51471 2156.86301) (17814.16810 2152.93710) (17812.96946 1315.98699)))
("SF_PLANTING" 0 ((17926.09163 4177.97930) (17921.12466 4151.58371) (17841.94050 4019.60826) (17823.38824 3996.98382)
(17814.85860 3955.50486)))
("SF_PLANTING" 0 ((17814.85860 3955.50486) (17846.90611 3959.27602)))
("SF_PLANTING" 0 ((17816.74208 3753.77115) (17820.21776 3770.73948) (17816.74208 3808.44604)))
("SF_PLANTING" 0 ((17816.74208 3808.44604) (17850.67873 3815.98835)))
("SF_PLANTING" 0 ((17824.28167 3755.65611) (17816.74208 3753.77115)))
("SF_PLANTING" 0 ((17835.59389 3518.09955) (17816.74208 3521.87002)))
("SF_PLANTING" 0 ((17858.21833 897.43495) (17835.59389 902.40475) (17821.56968 912.66686) (17816.74208 923.83201)))
("SF_PLANTING" 0 ((17816.74208 923.83201) (17828.05430 931.21833) (17860.10747 933.25792)))
("SF_PLANTING" 0 ((17831.82692 3891.40271) (17820.51471 3891.40271)))
("SF_ARCHITECTURE" 0 ((17820.51471 2156.86301) (17824.43778 2171.79106) (17839.36652 2175.71618)))
("SF_ARCHITECTURE" 0 ((17820.51471 2156.86301) (17831.81855 2158.06708) (17839.36652 2168.17523)))
("SF_ARCHITECTURE" 0 ((17835.59389 5007.54106) (17824.28167 5007.54106)))
("SF_PLANTING" 0 ((17824.28167 3755.65611) (17850.67873 3755.65611)))
("SF_PLANTING" 0 ((17824.28167 3755.65611) (17839.36652 3710.40724)))
("SF_PLANTING" 0 ((17828.05430 3552.03620) (17835.59389 3518.09955)))
("SF_PLANTING" 0 ((17869.53054 3585.97285) (17835.74446 3578.27647) (17829.11063 3567.11889) (17828.05430 3552.03620)))
("SF_PLANTING" 0 ((17831.82692 558.06844) (17828.05430 509.04977)))
("SF_PLANTING" 0 ((18736.80430 512.81957) (18721.71946 509.05600) (17828.05430 509.04977)))
("SF_PLANTING" 0 ((17846.90611 3868.77828) (17831.82692 3891.40271)))
("SF_PLANTING" 0 ((17937.40385 3865.00713) (17922.32466 3882.81120) (17869.53054 3910.10204) (17850.67873 3907.38066)
(17831.82692 3891.40271)))
("SF_PLANTING" 0 ((17850.67873 3653.84615) (17831.82692 3653.84615)))
("SF_PLANTING" 0 ((17835.59389 3518.09955) (17839.36652 3487.93337)))
("SF_PLANTING" 0 ((17843.13914 3352.18676) (17839.36652 3352.18676) (17835.59389 3359.72851)))
("SF_PLANTING" 0 ((17850.67873 3397.43563) (17841.94604 3367.27647) (17835.59389 3359.72851)))
("SF_PLANTING" 0 ((17839.36652 3702.86618) (17839.36652 3710.40724)))
("SF_PLANTING" 0 ((17865.76357 3721.71946) (17839.36652 3710.40724)))
("SF_PLANTING" 0 ((17850.67873 3653.84615) (17846.75973 3687.78281) (17839.36652 3702.86618)))
("SF_PLANTING" 0 ((17873.30317 3487.93337) (17839.36652 3487.93337)))
("SF_PLANTING" 0 ((17839.36652 3212.66968) (17839.36652 3231.52364)))
("SF_ARCHITECTURE" 0 ((17839.36652 2168.17523) (17839.36652 2175.71618)))
("SF_ARCHITECTURE" 0 ((17861.99095 2187.02839) (17847.05667 2185.82432) (17839.36652 2175.71618)))
("SF_ARCHITECTURE" 0 ((17861.99095 2179.48744) (17854.44299 2169.37930) (17839.36652 2168.17523)))
("SF_PLANTING" 0 ((17843.13914 1014.32975) (17843.28552 980.39310) (17860.10747 933.25792)))
("SF_PLANTING" 0 ((17843.13914 1014.32975) (17888.38801 1025.64197)))
("SF_PLANTING" 0 ((17843.13914 806.93722) (17880.84276 799.39762)))
("SF_PLANTING" 0 ((17843.13914 806.93722) (17843.13914 795.62500)))
("SF_PLANTING" 0 ((17843.13914 795.62500) (17844.19412 784.31278) (17850.82647 773.00057) (17861.99095 762.88699)
(17877.07579 757.91855)))
("SF_PLANTING" 0 ((17963.80090 3940.42274) (17914.77941 3940.57059) (17858.21833 3948.11844) (17846.90611 3959.27602)))
("SF_PLANTING" 0 ((17846.90611 3959.27602) (17854.45543 3970.44016) (17869.53054 3980.70905) (17899.70023 3989.29367)
(17922.32466 3989.43529) (17944.79853 3980.84378) (17957.30803 3959.43066) (17963.80090 3955.50486)))
("SF_PLANTING" 0 ((17846.90611 3868.77828) (17858.21833 3867.57376) (17872.09898 3853.69559) (17873.30317 3842.38269)))
("SF_PLANTING" 0 ((17846.90611 3868.77828) (17850.67873 3838.61278)))
("SF_PLANTING" 0 ((17861.99095 889.89536) (17883.41120 882.19830) (17886.13156 859.88314) (17880.83314 856.11199)
(17858.21833 856.11199) (17846.90611 867.27093)))
("SF_PLANTING" 0 ((17861.99095 889.89536) (17846.90611 867.27093)))
("SF_PLANTING" 0 ((17850.67873 3815.98835) (17850.67873 3838.61278)))
("SF_PLANTING" 0 ((17850.67873 3838.61278) (17873.30317 3842.38269)))
("SF_PLANTING" 0 ((17850.67873 3815.98835) (17858.21833 3800.90498)))
("SF_PLANTING" 0 ((17865.76357 3721.71946) (17864.70577 3733.03167) (17850.67873 3755.65611)))
("SF_PLANTING" 0 ((17850.67873 3755.65611) (17858.21833 3800.90498)))
("SF_PLANTING" 0 ((17850.67873 3653.84615) (17873.30317 3653.84615)))
("SF_PLANTING" 0 ((17850.67873 3397.43563) (17836.65170 3405.12579) (17832.12794 3416.28337) (17839.37342 3424.72613)
(17854.45136 3427.60181)))
("SF_PLANTING" 0 ((17858.21833 3412.51912) (17850.67873 3397.43563)))
("SF_PLANTING" 0 ((17858.21833 3412.51912) (17858.21833 3423.83133) (17854.45136 3427.60181)))
("SF_PLANTING" 0 ((17873.30317 3442.68450) (17858.37443 3438.75939) (17854.45136 3427.60181)))
("SF_PLANTING" 0 ((17880.84276 3808.44604) (17873.29627 3802.10260) (17858.21833 3800.90498)))
("SF_PLANTING" 0 ((17918.55204 3371.04072) (17892.15498 3376.01538) (17869.38416 3404.97048) (17858.21833 3412.51912)))
("SF_PLANTING" 0 ((17861.99095 889.89536) (17858.21833 897.43495)))
("SF_PLANTING" 0 ((17858.21833 897.43495) (17860.10747 933.25792)))
("SF_PLANTING" 0 ((18499.24774 935.14423) (17933.63688 937.71606) (17860.10747 933.25792)))
("SF_ARCHITECTURE" 0 ((17861.99095 2179.48744) (17861.99095 2187.02839)))
("SF_ARCHITECTURE" 0 ((17884.61538 2198.34061) (17869.68111 2197.13654) (17861.99095 2187.02839)))
("SF_ARCHITECTURE" 0 ((17861.99095 2179.48744) (17877.06742 2182.36312) (17884.61538 2190.79966)))
("SF_PLANTING" 0 ((17861.99095 1108.59729) (17883.55905 1067.11821) (17888.38801 1025.64197)))
("SF_PLANTING" 0 ((17880.84276 1116.13971) (17865.91686 1114.94106) (17861.99095 1108.59729)))
("SF_PLANTING" 0 ((17861.99095 697.58767) (17880.84276 693.81505)))
("SF_ARCHITECTURE" 0 ((17865.76357 4298.64253) (17872.11290 4302.56765) (17912.06742 4373.90905) (17936.34887
4396.68133) (17976.16256 4464.54842) (17997.58982 4483.40916) (18020.36199 4517.34581)))
("SF_PLANTING" 0 ((17865.76357 3721.71946) (17880.84276 3717.94830)))
("SF_PLANTING" 0 ((17865.76357 3152.33812) (17869.53054 3144.79638)))
("SF_ARCHITECTURE" 0 ((17865.76357 1463.04581) (17872.25373 1466.97172) (17923.52048 1557.30860) (17944.79299
1572.54661) (17956.26131 1595.02262)))
("SF_PLANTING" 0 ((17873.30317 629.71346) (17865.76357 629.71346)))
("SF_PLANTING" 0 ((17869.53054 3585.97285) (17873.30317 3552.03620)))
("SF_PLANTING" 0 ((17869.53054 3585.97285) (17877.07579 3601.05554)))
("SF_PLANTING" 0 ((17880.84276 3842.38269) (17873.30317 3842.38269)))
("SF_PLANTING" 0 ((17873.30317 3653.84615) (17877.07579 3601.05554)))
("SF_PLANTING" 0 ((17873.30317 3653.84615) (17892.15498 3676.47059)))
("SF_PLANTING" 0 ((17873.30317 3552.03620) (17895.92070 3547.06154) (17907.23982 3529.41176)))
("SF_PLANTING" 0 ((17873.30317 3552.03620) (17873.30317 3518.09955)))
("SF_PLANTING" 0 ((17873.30317 3487.93337) (17873.30317 3518.09955)))
("SF_PLANTING" 0 ((17907.23982 3529.41176) (17895.92070 3519.30373) (17873.30317 3518.09955)))
("SF_PLANTING" 0 ((17873.30317 3487.93337) (17873.30317 3480.39242)))
("SF_PLANTING" 0 ((17933.63688 3480.39242) (17873.30317 3480.39242)))
("SF_PLANTING" 0 ((17873.30317 3442.68450) (17873.30317 3480.39242)))
("SF_PLANTING" 0 ((17918.55204 3371.04072) (17913.57670 3404.97738) (17884.46765 3437.85769) (17873.30317 3442.68450)))
("SF_PLANTING" 0 ((17914.77941 3604.82681) (17877.07579 3601.05554)))
("SF_PLANTING" 0 ((17892.15498 3299.39695) (17877.07579 3299.39695)))
("SF_PLANTING" 0 ((17888.38801 3227.75238) (17877.22217 3254.14808) (17873.31561 3288.08473) (17877.07579 3299.39695)))
("SF_PLANTING" 0 ((17877.07579 757.91855) (17884.61538 746.60633)))
("SF_PLANTING" 0 ((17880.84276 799.39762) (17877.07579 757.91855)))
("SF_PLANTING" 0 ((18001.51018 4046.00260) (17975.11312 4053.39649) (17963.80090 4052.49446) (17880.84276 4015.83710)))
("SF_PLANTING" 0 ((17892.15498 3842.38269) (17880.84276 3842.38269)))
("SF_PLANTING" 0 ((17880.84276 3842.38269) (17880.84276 3808.44604)))
("SF_PLANTING" 0 ((17933.63688 3819.75826) (17914.77941 3819.61041) (17880.84276 3808.44604)))
("SF_PLANTING" 0 ((17880.84276 3717.94830) (17892.15498 3676.47059)))
("SF_PLANTING" 0 ((17880.84276 3717.94830) (17895.92760 3729.26052)))
("SF_PLANTING" 0 ((17880.84276 1116.13971) (17888.39208 1106.02466) (17899.70023 1102.10577) (17929.86425 1101.05486)))
("SF_PLANTING" 0 ((17880.84276 1116.13971) (17895.92760 1130.01686) (17918.54514 1130.01686) (17924.89581 1123.67443)
(17929.86425 1101.05486)))
("SF_PLANTING" 0 ((17880.84276 799.39762) (17888.38801 822.02206)))
("SF_PLANTING" 0 ((17880.84276 693.81505) (17899.70023 656.10860)))
("SF_PLANTING" 0 ((17880.84276 693.81505) (17891.86086 723.98190) (17884.61538 746.60633)))
("SF_ARCHITECTURE" 0 ((17884.61538 2198.34061) (17884.61538 2190.79966)))
("SF_ARCHITECTURE" 0 ((17884.61538 2198.34061) (17892.30554 2208.44876) (17907.23982 2209.65283)))
("SF_ARCHITECTURE" 0 ((17911.01244 2202.11188) (17895.92760 2191.85600) (17884.61538 2190.79966)))
("SF_PLANTING" 0 ((17978.88575 1157.61595) (17963.80090 1158.66686) (17918.55204 1172.55238) (17907.23982 1171.64989)
(17884.61538 1161.38857)))
("SF_PLANTING" 0 ((17895.92760 750.37613) (17884.61538 746.60633)))
("SF_PLANTING" 0 ((17971.34050 1021.86934) (17952.48869 1014.47749) (17922.32466 1014.47681) (17888.38801 1025.64197)))
("SF_ARCHITECTURE" 0 ((17903.46719 5041.47771) (17892.15498 5041.47771)))
("SF_PLANTING" 0 ((17911.01244 3672.69943) (17892.15498 3676.47059)))
("SF_PLANTING" 0 ((18608.59729 3276.77251) (17914.77941 3280.54989) (17903.46719 3284.46810) (17892.15498 3299.39695)))
("SF_PLANTING" 0 ((18783.93665 3303.16742) (18748.11652 3306.93167) (17941.17647 3306.93167) (17892.15498 3299.39695)))
("SF_PLANTING" 0 ((17895.92760 3729.26052) (17918.40430 3716.89910) (17926.09163 3706.63609)))
("SF_PLANTING" 0 ((17895.92760 3729.26052) (17893.36052 3766.96210) (17899.70430 3773.30554) (17918.55204 3774.50939)))
("SF_PLANTING" 0 ((18665.15837 569.38066) (18582.20023 569.38756) (18559.57579 573.15328) (18476.62330 573.00486)
(18461.53846 569.38756) (17899.70023 569.38066)))
("SF_PLANTING" 0 ((17907.23982 3529.41176) (17918.55204 3528.35543) (17932.43133 3518.09333) (17933.63688 3480.39242)))
("SF_ARCHITECTURE" 0 ((17911.01244 2202.11188) (17907.23982 2209.65283)))
("SF_ARCHITECTURE" 0 ((17937.40385 2217.19457) (17918.55894 2220.81041) (17907.23982 2209.65283)))
("SF_PLANTING" 0 ((17911.01244 3672.69943) (17912.06742 3661.38722) (17924.88201 3634.99287) (17914.77941 3604.82681)))
("SF_PLANTING" 0 ((17911.01244 3672.69943) (17926.09163 3695.32387)))
("SF_ARCHITECTURE" 0 ((17937.40385 2217.19457) (17929.71652 2207.08032) (17911.01244 2202.11188)))
("SF_PLANTING" 0 ((17926.09163 3582.20238) (17914.77941 3604.82681)))
("SF_ARCHITECTURE" 0 ((17914.77941 1651.58371) (17941.32421 1689.28529) (17958.98156 1704.37986) (18013.86912
1791.10011) (18030.62477 1806.33201) (18076.92308 1877.82805)))
("SF_ARCHITECTURE" 0 ((17918.55204 5052.78993) (17926.10000 5051.58609) (17937.40385 5041.47771)))
("SF_ARCHITECTURE" 0 ((17918.55204 4487.17907) (17937.55441 4517.34514) (17960.02828 4532.42794)))
("SF_PLANTING" 0 ((17918.55204 3371.04072) (17918.55204 3359.72851) (17922.32466 3355.95803)))
("SF_PLANTING" 0 ((17926.09163 4177.97930) (17933.63688 4181.74921)))
("SF_PLANTING" 0 ((17926.09163 3695.32387) (17926.09163 3706.63609)))
("SF_PLANTING" 0 ((17986.42534 3695.32387) (17933.64095 3710.11075) (17926.09163 3706.63609)))
("SF_PLANTING" 0 ((17926.09163 3695.32387) (17937.40385 3687.78281)))
("SF_PLANTING" 0 ((17929.86425 1101.05486) (17948.71606 1083.40645) (17967.57353 1078.43043)))
("SF_PLANTING" 0 ((17971.34050 3763.19717) (17957.45713 3778.28054) (17933.63688 3819.75826)))
("SF_PLANTING" 0 ((17937.40385 3865.00713) (17931.06007 3846.15385) (17933.63688 3819.75826)))
("SF_PLANTING" 0 ((17944.94910 3446.45577) (17933.63688 3480.39242)))
("SF_ARCHITECTURE" 0 ((18129.71154 4091.25147) (18129.71991 4743.59016) (18133.48416 4766.21459) (18129.71991
4954.75113) (18133.47726 4973.60441) (18133.33643 5064.10215) (18125.78846 5081.75192) (18095.77489 5082.80826)
(17986.42534 5059.27590) (17937.40385 5041.47771)))
("SF_PLANTING" 0 ((17937.40385 3865.00713) (17986.42534 3865.16210) (18001.51018 3872.54943)))
("SF_ARCHITECTURE" 0 ((18133.48416 1251.88631) (18133.48416 2205.88235) (18133.48416 2239.81900) (18133.48416
2250.97658) (18122.16505 2254.74706) (18024.13462 2247.21222) (17975.11312 2234.99208) (17937.40385 2217.19457)))
("SF_PLANTING" 0 ((18634.99434 886.12274) (18559.57579 878.73020) (18484.16290 878.58801) (18442.68665 886.11787)
(18129.71154 882.35916) (18110.85973 886.11787) (17948.72443 886.27115) (17941.17647 889.89536)))
("SF_PLANTING" 0 ((17941.17647 754.14785) (17956.26131 754.14785) (18536.95136 754.14785) (18559.57579 754.14785)
(18627.44910 754.14785) (18638.76131 754.14785) (18650.07353 754.14785)))
("SF_PLANTING" 0 ((18627.44910 855.95871) (18604.82466 848.42251) (18024.13462 848.42251) (18009.04977 852.03903)
(17944.94910 852.18609)))
("SF_PLANTING" 0 ((18642.53394 629.71346) (18619.90950 629.71346) (17956.26131 629.71346) (17944.94910 629.71346)))
("SF_PLANTING" 0 ((17948.71606 799.39762) (17960.02828 803.01968) (18050.52602 803.17364) (18069.38348 806.93235)
(18159.88122 806.93235) (18174.96041 803.46357) (18190.04525 806.93235) (18442.68665 806.93235) (18461.53846 803.17364)
(18552.03620 803.16742) (18612.36991 806.93722)))
("SF_PLANTING" 0 ((17948.71606 686.27545) (17960.02828 690.03903) (18623.68213 690.05147) (18638.76131 693.81505)))
("SF_PLANTING" 0 ((17997.73756 4027.14932) (17990.18959 4023.52658) (17956.26131 4023.37817)))
("SF_ARCHITECTURE" 0 ((17967.57353 1617.64706) (17957.46403 1610.09977) (17956.26131 1595.02262)))
("SF_ARCHITECTURE" 0 ((17956.26131 1595.02262) (17971.18722 1599.84955) (17978.88575 1613.87726)))
("SF_ARCHITECTURE" 0 ((17960.02828 4532.42794) (17967.57353 4524.88688)))
("SF_ARCHITECTURE" 0 ((18069.38348 4698.34129) (18030.61787 4638.00905) (18002.70600 4607.84355) (17960.02828
4532.42794)))
("SF_PLANTING" 0 ((17963.80090 3940.42274) (17963.80090 3955.50486)))
("SF_PLANTING" 0 ((18016.58937 3955.50486) (17986.42534 3963.03405) (17963.80090 3955.50486)))
("SF_PLANTING" 0 ((17963.80090 3940.42274) (17975.12002 3925.48744) (17997.73756 3914.02715)))
("SF_PLANTING" 0 ((18020.36199 1221.71946) (18001.51018 1235.60430) (17990.19796 1236.64819) (17979.03213 1229.25430)
(17970.15158 1210.56188) (17963.80090 1206.63744)))
("SF_ARCHITECTURE" 0 ((17967.57353 1617.64706) (17978.88575 1613.87726)))
("SF_ARCHITECTURE" 0 ((17967.57353 1617.64706) (17972.39830 1636.49412) (17982.65271 1644.04129)))
("SF_PLANTING" 0 ((17971.34050 1021.86934) (17967.71991 1033.18156) (17967.57353 1078.43043)))
("SF_PLANTING" 0 ((18024.13462 1082.20305) (17982.65271 1082.05464) (17967.57353 1078.43043)))
("SF_PLANTING" 0 ((17971.34050 3763.19717) (17972.39830 3748.11505) (17986.27760 3717.94830) (17986.42534 3695.32387)))
("SF_PLANTING" 0 ((17971.34050 3763.19717) (18005.27715 3763.19762) (18061.83824 3763.19762) (18129.71154 3763.19762)
(18148.56900 3763.19762) (18495.47511 3763.19762) (18510.55995 3763.19762) (18529.41176 3763.19762) (18544.49661
3763.19762) (18589.74548 3763.19762) (18608.59729 3763.19762)))
("SF_PLANTING" 0 ((17971.34050 1021.86934) (18009.04977 1006.78733)))
("SF_PLANTING" 0 ((17978.88575 3367.27002) (18178.73303 3367.27002) (18201.35747 3367.27002) (18397.43778 3367.27002)
(18408.75000 3367.27002)))
("SF_ARCHITECTURE" 0 ((17990.19796 1638.38518) (17988.99242 1625.19152) (17978.88575 1613.87726)))
("SF_PLANTING" 0 ((17978.88575 1157.61595) (18009.04977 1132.41278) (18024.13462 1127.59898) (18050.52602 1127.45192)))
("SF_PLANTING" 0 ((17978.88575 1157.61595) (17986.42534 1168.92817)))
("SF_ARCHITECTURE" 0 ((17990.19796 1638.38518) (17982.65271 1644.04129)))
("SF_ARCHITECTURE" 0 ((17990.19796 1638.38518) (17986.42534 1636.50170) (17982.65271 1644.04129)))
("SF_PLANTING" 0 ((18005.27715 3585.97285) (18005.13077 3608.59729) (17995.31821 3642.52771) (18012.30452 3654.90283)
(18008.89649 3676.47059) (18001.50181 3687.62817) (17986.42534 3695.32387)))
("SF_PLANTING" 0 ((18657.61878 3397.43563) (18646.30656 3401.20068) (17986.42534 3401.20690)))
("SF_ARCHITECTURE" 0 ((17990.19796 1638.38518) (18001.36097 1647.81595) (18024.13462 1681.75057)))
("SF_PLANTING" 0 ((17997.73756 3914.02715) (18001.51018 3872.54943)))
("SF_PLANTING" 0 ((18016.58937 3955.50486) (18011.61686 3929.11052) (17997.73756 3914.02715)))
("SF_PLANTING" 0 ((18005.27715 3585.97285) (17997.73756 3582.20238)))
("SF_PLANTING" 0 ((18027.90158 1195.32523) (17997.73756 1191.55260)))
("SF_PLANTING" 0 ((18001.51018 3872.54943) (18031.67421 3865.15554) (18073.15045 3865.00713)))
("SF_PLANTING" 0 ((18653.84615 3435.14355) (18001.51018 3435.14355)))
("SF_PLANTING" 0 ((18005.27715 3585.97285) (18020.21425 3555.80667) (18016.58937 3536.95351)))
("SF_PLANTING" 0 ((18005.27715 3472.85068) (18092.00792 3472.85068) (18110.85973 3472.85068) (18141.02376 3472.85068)
(18159.88122 3472.85068) (18239.06674 3472.85068) (18261.69118 3472.85068) (18288.08258 3472.85068) (18450.22624
3476.61493) (18465.31109 3472.99842) (18567.12104 3470.27805) (18646.30656 3473.00532) (18657.61878 3480.39242)))
("SF_PLANTING" 0 ((18016.58937 972.85068) (18009.04977 1006.78733)))
("SF_PLANTING" 0 ((18073.15045 1025.64197) (18042.98643 1020.66595) (18031.67421 1011.76199) (18009.04977 1006.78733)))
("SF_PLANTING" 0 ((18016.58937 3955.50486) (18046.75905 3956.56154) (18061.83824 3966.81708)))
("SF_PLANTING" 0 ((18027.90158 1195.32523) (18045.70124 1168.92817) (18050.52602 1127.45192)))
("SF_PLANTING" 0 ((18031.67421 1202.86482) (18027.90158 1195.32523)))
("SF_PLANTING" 0 ((18031.67421 4004.52489) (18039.21380 4004.52489)))
("SF_PLANTING" 0 ((18035.44683 3808.44604) (18042.98643 3804.67613)))
("SF_PLANTING" 0 ((18061.83824 3966.81708) (18039.21380 4004.52489)))
("SF_PLANTING" 0 ((18039.21380 4004.52489) (18050.52602 4027.14932)))
("SF_PLANTING" 0 ((18042.98643 4087.48156) (18040.56708 4080.08111) (18069.37511 4057.31482) (18099.54751 4019.60826)))
("SF_PLANTING" 0 ((18046.75905 3921.56821) (18058.07127 3925.33937)))
("SF_PLANTING" 0 ((18076.92308 1119.90950) (18050.52602 1127.45192)))
("SF_ARCHITECTURE" 0 ((18054.29864 5663.65011) (18107.08710 5663.65011)))
("SF_PLANTING" 0 ((18073.15045 1195.32523) (18059.12624 1217.94966) (18054.29864 1266.96833)))
("SF_PLANTING" 0 ((18133.48416 1251.88631) (18107.09548 1252.03959) (18100.59695 1255.81075) (18058.07127 1323.52941)))
("SF_PLANTING" 0 ((18061.83824 3966.81708) (18080.69570 3966.81708)))
("SF_PLANTING" 0 ((18544.49661 3616.13903) (18533.33767 3617.34310) (18529.56505 3623.68688) (18531.97885 3687.62817)
(18510.55995 3695.17602) (18457.76584 3691.56018) (18159.88122 3691.55396) (18137.25679 3695.31075) (18099.54751
3691.55396) (18065.61086 3695.32387)))
("SF_PLANTING" 0 ((18499.24774 3650.07500) (18193.81787 3650.08190) (18167.42081 3653.84615) (18159.88122 3653.84615)
(18144.79638 3650.22342) (18103.32014 3653.83993) (18069.38348 3650.07500)))
("SF_PLANTING" 0 ((18469.07805 3616.13903) (18401.20475 3617.33620) (18352.18891 3623.67376) (18299.39480 3619.90950)
(18197.58484 3623.67376) (18122.17195 3616.14525) (18069.38348 3619.90950)))
("SF_PLANTING" 0 ((18665.15837 3582.20215) (18623.68213 3582.20215) (18567.12104 3582.20215) (18408.75000 3582.20215)
(18393.66516 3582.20215) (18378.58032 3582.20215) (18141.02376 3582.20215) (18103.32014 3582.20215) (18069.38348
3582.20215)))
("SF_PLANTING" 0 ((18129.71154 4091.25147) (18099.54751 4092.45622) (18059.27398 4132.73043) (18059.11799 4155.35486)
(18063.03688 4166.66018) (18073.15045 4174.20814)))
("SF_PLANTING" 0 ((18114.63235 3838.61278) (18099.54751 3843.43314) (18073.15045 3865.00713)))
("SF_PLANTING" 0 ((18125.94457 3887.63156) (18084.46267 3878.88597) (18073.15045 3865.00713)))
("SF_PLANTING" 0 ((18073.15045 1195.32523) (18090.95011 1157.61595) (18092.00792 1134.99152)))
("SF_PLANTING" 0 ((18129.71154 1191.55260) (18084.46267 1197.89706) (18073.15045 1195.32523)))
("SF_PLANTING" 0 ((18133.48416 1018.09955) (18084.46267 1018.25419) (18073.15045 1025.64197)))
("SF_PLANTING" 0 ((18107.08710 1067.11821) (18095.77489 1057.01086) (18081.75068 1051.88156) (18073.15045 1025.64197)))
("SF_PLANTING" 0 ((18672.69796 3529.41176) (18665.15147 3533.03450) (18601.05769 3533.32998) (18582.20023 3536.95351)
(18552.03620 3533.18247) (18088.23529 3533.18247) (18076.92308 3533.18247)))
("SF_PLANTING" 0 ((18076.92308 1119.90950) (18096.83269 1078.43043) (18107.08710 1067.11821)))
("SF_PLANTING" 0 ((18076.92308 1119.90950) (18092.00792 1134.99152)))
("SF_PLANTING" 0 ((18080.69570 3966.81708) (18081.89842 3951.74118) (18088.24219 3945.39084) (18125.94457 3932.88043)))
("SF_PLANTING" 0 ((18131.60068 3995.09762) (18099.54751 3988.23767) (18080.69570 3966.81708)))
("SF_ARCHITECTURE" 0 ((18092.00792 5324.28314) (18099.39977 5301.65871) (18099.54751 5267.72206)))
("SF_ARCHITECTURE" 0 ((18092.00792 5324.28314) (18088.08756 5365.76210) (18077.07081 5414.78088) (18077.07636
5433.63473) (18080.84898 5441.02183) (18092.00792 5444.94072) (18250.37896 5444.79265) (18257.75701 5441.02183)
(18260.48563 5433.63473) (18242.83371 5324.28314)))
("SF_ARCHITECTURE" 0 ((18092.00792 2503.77048) (18103.02319 2462.29287) (18099.54751 2447.20939)))
("SF_ARCHITECTURE" 0 ((18092.00792 2503.77048) (18091.85871 2537.70713) (18080.84898 2616.89265) (18092.00792
2630.77195) (18239.06674 2631.96991) (18253.99265 2627.14853) (18257.76527 2620.65701) (18257.77081 2598.03948)
(18246.75407 2541.47839) (18246.60633 2503.77048)))
("SF_PLANTING" 0 ((18092.00792 1134.99152) (18125.94457 1134.99152)))
("SF_ARCHITECTURE" 0 ((18235.29412 5267.72206) (18223.98190 5253.84378) (18212.66968 5252.63993) (18186.27262
5256.26199) (18110.85973 5256.56482) (18099.54751 5267.72206)))
("SF_ARCHITECTURE" 0 ((18239.06674 2450.98066) (18227.60396 2433.18303) (18212.66968 2428.36244) (18114.63235
2432.28133) (18099.54751 2447.20939)))
("SF_PLANTING" 0 ((18103.32014 588.23529) (18122.17195 588.23529)))
("SF_PLANTING" 0 ((18107.08710 1067.11821) (18125.94457 1067.11821)))
("SF_PLANTING" 0 ((18122.17195 3808.44604) (18114.78563 3819.75894) (18114.63235 3838.61278)))
("SF_PLANTING" 0 ((18141.02376 3853.69491) (18114.63235 3838.61278)))
("SF_PLANTING" 0 ((18125.94457 3925.33937) (18125.94457 3932.88043)))
("SF_PLANTING" 0 ((18137.25679 3966.81708) (18132.28835 3940.42896) (18125.94457 3932.88043)))
("SF_PLANTING" 0 ((18171.19344 3925.33937) (18125.94457 3925.33937)))
("SF_PLANTING" 0 ((18125.94457 3887.63156) (18125.94457 3925.33937)))
("SF_PLANTING" 0 ((18137.25679 3887.63156) (18125.94457 3887.63156)))
("SF_PLANTING" 0 ((18137.25679 1112.36708) (18125.94457 1134.99152)))
("SF_PLANTING" 0 ((18129.71154 1191.55260) (18137.09378 1165.15837) (18125.94457 1134.99152)))
("SF_PLANTING" 0 ((18125.94457 1067.11821) (18133.48416 1063.34842)))
("SF_PLANTING" 0 ((18137.25679 1112.36708) (18136.19898 1085.97285) (18125.94457 1067.11821)))
("SF_PLANTING" 0 ((18129.71154 4091.25147) (18129.71154 4061.08597)))
("SF_PLANTING" 0 ((18129.71154 4061.08597) (18167.42081 4057.31482)))
("SF_PLANTING" 0 ((18131.60068 3995.09762) (18129.71154 4061.08597)))
("SF_PLANTING" 0 ((18133.48416 1251.88631) (18133.48416 1225.48925) (18129.71154 1191.55260)))
("SF_PLANTING" 0 ((18131.60068 3995.09762) (18137.25679 3966.81708)))
("SF_PLANTING" 0 ((18131.60068 3995.09762) (18167.42081 3996.98382)))
("SF_PLANTING" 0 ((18159.88122 1063.34842) (18133.48416 1063.34842)))
("SF_PLANTING" 0 ((18133.48416 1018.09955) (18133.48416 1063.34842)))
("SF_PLANTING" 0 ((18220.20928 1018.09955) (18205.13009 1014.32975) (18144.79638 1014.47681) (18133.48416 1018.09955)))
("SF_PLANTING" 0 ((18137.25679 3966.81708) (18167.27308 3968.02183) (18178.73303 3981.90045)))
("SF_PLANTING" 0 ((18137.25679 3887.63156) (18141.02376 3853.69491)))
("SF_PLANTING" 0 ((18137.25679 3887.63156) (18174.96041 3892.60690) (18186.27262 3902.71493)))
("SF_PLANTING" 0 ((18137.25679 1112.36708) (18171.19152 1116.13971)))
("SF_PLANTING" 0 ((18212.66968 3861.23722) (18197.58484 3851.12885) (18178.73303 3846.30192) (18141.02376 3853.69491)))
("SF_PLANTING" 0 ((18159.88122 1063.34842) (18167.42771 1059.72568) (18205.13009 1059.57862)))
("SF_PLANTING" 0 ((18159.88122 1063.34842) (18171.19152 1078.43043) (18171.19152 1093.51527)))
("SF_PLANTING" 0 ((18174.96041 4038.46154) (18167.42081 4057.31482)))
("SF_PLANTING" 0 ((18171.19344 4068.62704) (18167.42081 4057.31482)))
("SF_PLANTING" 0 ((18167.42081 3996.98382) (18178.73303 3981.90045)))
("SF_PLANTING" 0 ((18171.19344 4019.60826) (18167.42081 3996.98382)))
("SF_PLANTING" 0 ((18171.19152 1217.94966) (18171.19152 1199.09502)))
("SF_PLANTING" 0 ((18205.13009 1199.09502) (18171.19152 1199.09502)))
("SF_PLANTING" 0 ((18171.19152 1199.09502) (18171.19152 1191.54774) (18171.19152 1131.22172) (18171.19152 1116.13971)))
("SF_PLANTING" 0 ((18171.19152 1093.51527) (18171.19152 1116.13971)))
("SF_PLANTING" 0 ((18212.66968 1093.51527) (18171.19152 1093.51527)))
("SF_PLANTING" 0 ((18171.19344 3951.73495) (18171.19344 3925.33937)))
("SF_PLANTING" 0 ((18186.27262 3902.71493) (18171.19344 3925.33937)))
("SF_ARCHITECTURE" 0 ((18178.73303 5663.65011) (18208.89706 5663.65011) (18578.43326 5663.65011)))
("SF_PLANTING" 0 ((18208.89706 3981.90045) (18178.73303 3981.90045)))
("SF_PLANTING" 0 ((18197.58484 3902.71493) (18186.27262 3902.71493)))
("SF_PLANTING" 0 ((18197.58484 3902.71493) (18212.66968 3872.54943)))
("SF_PLANTING" 0 ((18212.66968 3929.11052) (18211.46550 3921.56199) (18197.58484 3902.71493)))
("SF_PLANTING" 0 ((18205.13009 1199.09502) (18208.89299 1187.78281) (18206.32590 1146.30373) (18212.52195 1127.45192)
(18213.86550 1104.83235) (18220.20928 1097.28507)))
("SF_ARCHITECTURE" 0 ((18533.18439 1263.19853) (18532.12658 2145.55079) (18521.86380 2160.47885) (18476.62330
2185.83744) (18374.81335 2231.22783) (18291.85520 2250.98348) (18220.20928 2254.74706) (18212.82296 2250.97658)
(18208.90543 2239.81900) (18208.89299 1319.75962) (18205.13009 1297.13518) (18208.75068 1278.28054) (18208.89299
1214.17704) (18205.13009 1199.09502)))
("SF_PLANTING" 0 ((18220.20928 1018.09955) (18211.47941 1052.02930) (18205.13009 1059.57862)))
("SF_PLANTING" 0 ((18212.66968 1093.51527) (18205.13009 1059.57862)))
("SF_PLANTING" 0 ((18212.66968 3929.11052) (18212.52195 3970.58824) (18208.89706 3981.90045)))
("SF_PLANTING" 0 ((18208.89898 3993.21267) (18208.89706 3981.90045)))
("SF_ARCHITECTURE" 0 ((18208.89898 3993.21267) (18208.89898 4008.29604) (18210.10260 5075.40814) (18220.20928
5082.80170) (18254.14593 5082.80826) (18359.72851 5059.28179) (18461.53846 5017.66256) (18525.63914 4981.14672)))
("SF_PLANTING" 0 ((18208.89898 3993.21267) (18246.60633 4000.75373)))
("SF_PLANTING" 0 ((18212.66968 3929.11052) (18246.60633 3933.03541) (18265.45814 3940.42274)))
("SF_PLANTING" 0 ((18212.66968 3861.23722) (18212.66968 3872.54943)))
("SF_PLANTING" 0 ((18314.47964 3880.09050) (18231.52149 3879.94242) (18212.66968 3872.54943)))
("SF_PLANTING" 0 ((18314.47964 3849.92500) (18227.75452 3853.84989) (18212.66968 3861.23722)))
("SF_PLANTING" 0 ((18212.66968 1093.51527) (18220.20928 1097.28507)))
("SF_PLANTING" 0 ((18227.75452 1097.28507) (18220.20928 1097.28507)))
("SF_PLANTING" 0 ((18220.20928 1018.09955) (18261.69118 1018.09955)))
("SF_PLANTING" 0 ((18227.75452 1097.28507) (18239.06674 1086.12749) (18288.08258 1089.74265)))
("SF_PLANTING" 0 ((18227.75452 1097.28507) (18265.30486 1138.76414) (18273.15667 1153.83993) (18291.85520 1167.73100)
(18318.25226 1169.98529) (18340.87670 1180.22794) (18363.50113 1168.92817)))
("SF_ARCHITECTURE" 0 ((18235.29412 5267.72206) (18284.31561 5263.80373) (18337.10407 5251.58948) (18469.07805
5206.19943) (18559.57579 5157.32127) (18604.82466 5127.15509) (18668.93100 5076.47104) (18695.32240 5067.87330)))
("SF_ARCHITECTURE" 0 ((18235.29412 5267.72206) (18242.83371 5324.28314)))
("SF_ARCHITECTURE" 0 ((18668.93100 2243.58948) (18570.88801 2325.49672) (18499.24774 2370.74559) (18461.53846
2389.74038) (18359.72851 2427.29977) (18239.06674 2450.98066)))
("SF_ARCHITECTURE" 0 ((18239.06674 2450.98066) (18239.21312 2488.68778) (18246.60633 2503.77048)))
("SF_ARCHITECTURE" 0 ((18242.83371 5324.28314) (18276.77036 5324.13529) (18340.87670 5311.91550) (18416.28959
5289.29106) (18472.85068 5266.52477) (18593.51244 5198.79333) (18634.99434 5169.53518) (18676.47059 5133.18020)
(18699.09502 5128.20554)))
("SF_ARCHITECTURE" 0 ((18246.60633 2503.77048) (18291.85520 2499.85226) (18359.72851 2483.86086) (18480.39027
2438.47738) (18555.80882 2397.14061) (18623.68213 2349.02217) (18680.24321 2301.20701) (18699.09502 2296.38009)))
("SF_PLANTING" 0 ((18257.91855 4279.78925) (18262.88009 4294.87138) (18314.47964 4381.59921)))
("SF_ARCHITECTURE" 0 ((18318.25226 1561.08597) (18307.99502 1549.77376) (18257.91855 1459.27602)))
("SF_PLANTING" 0 ((18329.56448 1029.41176) (18318.25226 1019.29751) (18303.16742 1014.47681) (18269.23767 1014.47681)
(18261.69118 1018.09955)))
("SF_PLANTING" 0 ((18280.54299 1048.26640) (18270.28710 1044.34050) (18261.69118 1018.09955)))
("SF_PLANTING" 0 ((18273.00339 3932.88043) (18265.45814 3940.42274)))
("SF_PLANTING" 0 ((18269.23077 3955.50486) (18265.45814 3940.42274)))
("SF_PLANTING" 0 ((18265.45814 588.23529) (18344.64367 588.23529) (18352.18891 588.23529) (18382.35294 588.23529)))
("SF_PLANTING" 0 ((18284.31561 3970.58824) (18280.54299 3963.04717)))
("SF_PLANTING" 0 ((18306.94005 3925.33937) (18284.31561 3921.56821)))
("SF_PLANTING" 0 ((18306.94005 1082.20305) (18288.08258 1089.74265)))
("SF_PLANTING" 0 ((18359.72851 1112.36708) (18350.98337 1134.84446) (18340.87670 1141.47138) (18333.33145 1141.32907)
(18299.54536 1119.76109) (18289.14038 1101.05486) (18288.08258 1089.74265)))
("SF_PLANTING" 0 ((18329.56448 4004.52489) (18314.47964 4003.46821) (18295.62783 3989.44152)))
("SF_PLANTING" 0 ((18306.94005 3925.33937) (18318.25226 3919.14400) (18344.64367 3925.19129) (18363.50113 3921.56821)))
("SF_PLANTING" 0 ((18306.94005 3925.33937) (18310.86312 3947.81572) (18344.64367 3965.76753) (18363.50113 3965.76165)
(18386.12557 3958.07183) (18397.43778 3947.96380)))
("SF_PLANTING" 0 ((18329.56448 1029.41176) (18311.75792 1052.03620) (18306.94005 1082.20305)))
("SF_PLANTING" 0 ((18359.72851 1112.36708) (18306.94005 1082.20305)))
("SF_ARCHITECTURE" 0 ((18348.41629 4528.65803) (18314.47964 4479.63801)))
("SF_ARCHITECTURE" 0 ((18314.47964 4381.59921) (18329.56448 4375.41595) (18339.67115 4385.36912) (18340.87670
4396.68133)))
("SF_ARCHITECTURE" 0 ((18314.47964 4381.59921) (18322.16290 4396.52738) (18329.56448 4400.45249)))
("SF_PLANTING" 0 ((18314.47964 3849.92500) (18314.47964 3880.09050)))
("SF_PLANTING" 0 ((18314.47964 3880.09050) (18355.95588 3883.86165)))
("SF_PLANTING" 0 ((18314.47964 3849.92500) (18322.01923 3846.15385)))
("SF_ARCHITECTURE" 0 ((18314.47964 1659.12613) (18352.18891 1715.68722)))
("SF_PLANTING" 0 ((18318.25226 3834.84163) (18322.01923 3846.15385)))
("SF_ARCHITECTURE" 0 ((18318.25226 1561.08597) (18325.79876 1556.56844) (18333.17817 1557.61787) (18337.10407
1572.39819)))
("SF_ARCHITECTURE" 0 ((18318.25226 1561.08597) (18322.01923 1568.62839) (18329.56448 1572.39819)))
("SF_PLANTING" 0 ((18322.01923 3846.15385) (18348.40939 3846.30192) (18355.95588 3849.92500)))
("SF_ARCHITECTURE" 0 ((18340.87670 4396.68133) (18329.56448 4400.45249)))
("SF_ARCHITECTURE" 0 ((18363.50113 4472.09695) (18330.76719 4415.53586) (18329.56448 4400.45249)))
("SF_ARCHITECTURE" 0 ((18329.56448 1572.39819) (18337.10407 1572.39819)))
("SF_ARCHITECTURE" 0 ((18329.56448 1572.39819) (18330.61946 1583.70419) (18337.10407 1591.25283)))
("SF_PLANTING" 0 ((18329.56448 1214.17704) (18348.56403 1236.65441) (18367.26810 1247.05803) (18420.06222 1251.88631)))
("SF_PLANTING" 0 ((18329.56448 1029.41176) (18371.04072 1029.56640) (18386.12557 1036.95419)))
("SF_ARCHITECTURE" 0 ((18337.10407 1591.25283) (18348.41629 1587.48020)))
("SF_ARCHITECTURE" 0 ((18352.18891 1617.64706) (18342.07941 1610.09977) (18337.10407 1591.25283)))
("SF_ARCHITECTURE" 0 ((18337.10407 1572.39819) (18347.21210 1579.94061) (18348.41629 1587.48020)))
("SF_ARCHITECTURE" 0 ((18412.51697 4509.80351) (18376.00916 4453.24242) (18362.30249 4423.07692) (18340.87670
4396.68133)))
("SF_ARCHITECTURE" 0 ((18348.41629 4528.65803) (18359.72851 4521.11572)))
("SF_ARCHITECTURE" 0 ((18363.50113 4551.28247) (18353.38473 4543.73394) (18348.41629 4528.65803)))
("SF_ARCHITECTURE" 0 ((18363.50113 1610.10464) (18362.29559 1598.79242) (18348.41629 1587.48020)))
("SF_ARCHITECTURE" 0 ((18359.72851 1696.83258) (18358.53269 1708.13857) (18352.18891 1715.68722)))
("SF_ARCHITECTURE" 0 ((18352.18891 1715.68722) (18353.39163 1723.23439) (18363.50113 1734.53903)))
("SF_ARCHITECTURE" 0 ((18352.18891 1617.64706) (18363.50113 1610.10464)))
("SF_ARCHITECTURE" 0 ((18363.50113 1651.58371) (18352.18891 1617.64706)))
("SF_PLANTING" 0 ((18355.95588 3849.92500) (18355.95588 3883.86165)))
("SF_PLANTING" 0 ((18363.50113 3887.63156) (18355.95588 3883.86165)))
("SF_PLANTING" 0 ((18386.12557 3849.92500) (18355.95588 3849.92500)))
("SF_PLANTING" 0 ((18389.89253 1112.36708) (18359.72851 1112.36708)))
("SF_ARCHITECTURE" 0 ((18363.50113 4551.28247) (18374.81335 4543.74016)))
("SF_ARCHITECTURE" 0 ((18363.50113 4551.28247) (18364.70385 4562.44627) (18374.81335 4570.13575)))
("SF_PLANTING" 0 ((18363.50113 3921.56821) (18359.73541 3910.25600) (18363.50113 3887.63156)))
("SF_PLANTING" 0 ((18363.50113 3921.56821) (18389.88846 3929.26448) (18396.23224 3936.65158) (18397.43778 3947.96380)))
("SF_PLANTING" 0 ((18374.81335 3887.63156) (18363.50113 3887.63156)))
("SF_ARCHITECTURE" 0 ((18374.81335 1730.76923) (18363.50113 1734.53903)))
("SF_ARCHITECTURE" 0 ((18374.81335 1749.62387) (18364.70385 1742.08145) (18363.50113 1734.53903)))
("SF_ARCHITECTURE" 0 ((18412.51697 1685.52036) (18376.01606 1628.95928) (18373.60781 1617.65396) (18363.50113
1610.10464)))
("SF_PLANTING" 0 ((18363.50113 1157.61595) (18363.50113 1168.92817)))
("SF_PLANTING" 0 ((18427.60181 1161.38857) (18404.97738 1166.35633) (18389.89253 1174.36471) (18363.50113 1168.92817)))
("SF_ARCHITECTURE" 0 ((18374.81335 1730.76923) (18371.04072 1715.68722)))
("SF_PLANTING" 0 ((18427.60181 1161.38857) (18426.54548 1184.01301) (18416.28269 1198.94038) (18393.66516 1209.35781)
(18371.04072 1214.17704)))
("SF_ARCHITECTURE" 0 ((18386.12557 4562.59468) (18374.81335 4570.13575)))
("SF_ARCHITECTURE" 0 ((18386.12557 4588.98903) (18376.01606 4577.68371) (18374.81335 4570.13575)))
("SF_ARCHITECTURE" 0 ((18374.81335 4532.42794) (18374.81335 4543.74016)))
("SF_ARCHITECTURE" 0 ((18386.12557 4562.59468) (18381.30351 4547.66595) (18374.81335 4543.74016)))
("SF_PLANTING" 0 ((18374.81335 3887.63156) (18385.06776 3872.54943) (18386.12557 3849.92500)))
("SF_PLANTING" 0 ((18386.12557 3902.71493) (18374.81335 3887.63156)))
("SF_ARCHITECTURE" 0 ((18374.81335 1749.62387) (18386.12557 1745.85124)))
("SF_ARCHITECTURE" 0 ((18374.81335 1749.62387) (18378.73643 1764.55124) (18389.89253 1768.47568)))
("SF_ARCHITECTURE" 0 ((18374.81335 1730.76923) (18384.92002 1738.31165) (18386.12557 1745.85124)))
("SF_ARCHITECTURE" 0 ((18386.12557 4588.98903) (18393.66516 4585.21912)))
("SF_ARCHITECTURE" 0 ((18386.12557 4588.98903) (18391.08563 4607.68857) (18397.43778 4611.61346)))
("SF_ARCHITECTURE" 0 ((18386.12557 4562.59468) (18392.46934 4570.14197) (18393.66516 4585.21912)))
("SF_PLANTING" 0 ((18438.91403 3857.46606) (18420.06222 3850.07285) (18386.12557 3849.92500)))
("SF_ARCHITECTURE" 0 ((18389.89253 1768.47568) (18393.36278 1760.92851) (18386.12557 1745.85124)))
("SF_PLANTING" 0 ((18386.12557 1134.99152) (18389.89253 1119.90950)))
("SF_PLANTING" 0 ((18431.37443 1029.41176) (18397.43778 1029.56640) (18386.12557 1036.95419)))
("SF_PLANTING" 0 ((18386.12557 1036.95419) (18393.51742 1063.34842) (18393.66516 1085.97285)))
("SF_ARCHITECTURE" 0 ((18404.97738 1794.87274) (18389.89253 1768.47568)))
("SF_PLANTING" 0 ((18427.60181 1108.59729) (18416.28959 1114.94106) (18389.89253 1119.90950)))
("SF_PLANTING" 0 ((18389.89253 1112.36708) (18389.89253 1119.90950)))
("SF_PLANTING" 0 ((18389.89253 1112.36708) (18393.66516 1085.97285)))
("SF_ARCHITECTURE" 0 ((18408.75000 4604.07240) (18404.82410 4592.76640) (18393.66516 4585.21912)))
("SF_PLANTING" 0 ((18423.82919 1093.51527) (18408.75000 1093.35995) (18393.66516 1085.97285)))
("SF_ARCHITECTURE" 0 ((18408.75000 4604.07240) (18397.43778 4611.61346)))
("SF_ARCHITECTURE" 0 ((18397.43778 4611.61346) (18401.20475 4619.15577)))
("SF_PLANTING" 0 ((18442.68665 3955.50486) (18416.28959 3948.11188) (18397.43778 3947.96380)))
("SF_ARCHITECTURE" 0 ((18412.51697 1802.41233) (18408.75000 1794.87274) (18404.97738 1794.87274)))
("SF_ARCHITECTURE" 0 ((18412.51697 1802.41233) (18404.97738 1798.64253) (18404.97738 1794.87274)))
("SF_ARCHITECTURE" 0 ((18408.75000 4604.07240) (18465.31109 4702.11120)))
("SF_ARCHITECTURE" 0 ((18465.31109 1877.82805) (18426.54548 1817.49717) (18412.51697 1802.41233)))
("SF_PLANTING" 0 ((18416.28959 4061.08597) (18378.58032 4060.93790) (18363.64751 4056.11753) (18353.39853 4038.46154)
(18363.64751 4019.76222) (18378.43394 4014.63292) (18397.43778 3994.41719) (18427.60181 3993.21267)))
("SF_PLANTING" 0 ((18423.82919 1093.51527) (18430.32353 1089.58937) (18446.45362 1063.34842)))
("SF_PLANTING" 0 ((18423.82919 1093.51527) (18427.60181 1108.59729)))
("SF_PLANTING" 0 ((18453.99887 4057.31482) (18442.68665 4049.93495) (18427.60181 4057.31482)))
("SF_PLANTING" 0 ((18427.60181 3993.21267) (18432.57025 3974.36561) (18442.68665 3966.81708)))
("SF_PLANTING" 0 ((18427.60181 3993.21267) (18431.37443 4023.37817)))
("SF_PLANTING" 0 ((18427.60181 1161.38857) (18428.80600 1153.83993) (18438.91403 1142.53394)))
("SF_PLANTING" 0 ((18427.60181 1108.59729) (18438.91403 1112.36708)))
("SF_PLANTING" 0 ((18431.37443 3367.27002) (18491.70249 3367.27002) (18503.01471 3367.27002) (18518.09955 3367.27002)
(18533.18439 3367.27002) (18555.80882 3367.27002) (18578.43326 3367.27002) (18668.93100 3367.27002) (18684.01018
3367.27002)))
("SF_PLANTING" 0 ((18431.37443 1029.41176) (18446.45362 1014.32975)))
("SF_PLANTING" 0 ((18431.37443 1029.41176) (18441.48801 1044.49378) (18446.45362 1063.34842)))
("SF_PLANTING" 0 ((18438.91403 3883.86165) (18476.62330 3883.71324) (18495.47511 3876.31934)))
("SF_PLANTING" 0 ((18438.91403 3883.86165) (18438.91403 3857.46606)))
("SF_PLANTING" 0 ((18446.45362 3944.19265) (18438.91403 3883.86165)))
("SF_PLANTING" 0 ((18491.70249 3853.69491) (18457.76584 3850.07285) (18438.91403 3857.46606)))
("SF_PLANTING" 0 ((18438.91403 1142.53394) (18438.91403 1112.36708)))
("SF_PLANTING" 0 ((18465.31109 1153.84615) (18461.38518 1147.50238) (18438.91403 1142.53394)))
("SF_PLANTING" 0 ((18514.32692 1108.59729) (18446.46199 1108.74502) (18438.91403 1112.36708)))
("SF_PLANTING" 0 ((18442.68665 3955.50486) (18442.68665 3966.81708)))
("SF_PLANTING" 0 ((18480.39027 4000.75373) (18442.68665 3966.81708)))
("SF_PLANTING" 0 ((18446.45362 3944.19265) (18442.68665 3955.50486)))
("SF_PLANTING" 0 ((18442.68665 987.93269) (18446.45362 1014.32975)))
("SF_PLANTING" 0 ((18446.45362 3944.19265) (18469.07805 3936.79966) (18495.47511 3936.65158)))
("SF_PLANTING" 0 ((18446.45362 1063.34842) (18472.85068 1063.34842)))
("SF_PLANTING" 0 ((18548.26357 1025.64197) (18521.87217 1010.70554) (18446.45362 1014.32975)))
("SF_PLANTING" 0 ((18465.31109 1180.24038) (18455.19468 1187.78971) (18450.22624 1202.86482)))
("SF_PLANTING" 0 ((18480.39027 4000.75373) (18479.33529 4012.06663) (18460.34819 4053.38993) (18453.99887 4057.31482)))
("SF_PLANTING" 0 ((18453.99887 4057.31482) (18456.57002 4106.33484) (18450.24005 4140.27149) (18454.15215 4151.57749)
(18469.07805 4158.97081) (18506.78733 4141.32817) (18529.41176 4136.50034)))
("SF_PLANTING" 0 ((18533.18439 1263.19853) (18506.79423 1274.66403) (18472.70294 1327.29921) (18457.76584 1341.17161)
(18450.23314 1341.17161) (18443.88937 1334.83473) (18442.83993 1327.29921) (18465.16188 1266.96833) (18461.53846
1230.51776)))
("SF_PLANTING" 0 ((18491.70249 3853.69491) (18479.19446 3815.98835) (18465.31109 3800.90498)))
("SF_PLANTING" 0 ((18465.31109 1180.24038) (18465.31109 1153.84615)))
("SF_PLANTING" 0 ((18465.31109 1180.24038) (18491.70249 1201.65452) (18499.23937 1198.93281) (18506.63405 1187.78281)
(18505.58314 1172.70079) (18499.23937 1165.30679) (18480.39027 1154.90249) (18465.31109 1153.84615)))
("SF_PLANTING" 0 ((18480.39027 4000.75373) (18510.55995 3989.44152)))
("SF_PLANTING" 0 ((18484.16290 3616.13903) (18503.01471 3616.13903)))
("SF_PLANTING" 0 ((18487.93552 4076.16934) (18494.28484 4068.62081) (18514.17364 4000.75441) (18510.55995 3989.44152)))
("SF_PLANTING" 0 ((18491.70249 3853.69491) (18499.24774 3857.46606)))
("SF_PLANTING" 0 ((18495.47511 3876.31934) (18495.47511 3936.65158)))
("SF_PLANTING" 0 ((18518.09955 3940.42274) (18495.47511 3936.65158)))
("SF_PLANTING" 0 ((18499.24774 3868.77828) (18495.47511 3876.31934)))
("SF_PLANTING" 0 ((18499.24774 3857.46606) (18499.24774 3868.77828)))
("SF_PLANTING" 0 ((18544.49661 3910.25600) (18499.24774 3868.77828)))
("SF_PLANTING" 0 ((18499.24774 3857.46606) (18567.12104 3846.30848) (18589.74548 3861.23722)))
("SF_PLANTING" 0 ((18499.24774 1048.26640) (18499.24774 1036.95419)))
("SF_PLANTING" 0 ((18499.24774 935.14423) (18499.24774 969.08088)))
("SF_PLANTING" 0 ((18499.24774 935.14423) (18529.41176 935.14423)))
("SF_PLANTING" 0 ((18510.55995 3989.44152) (18515.52002 3974.51335) (18521.87217 3970.58824)))
("SF_PLANTING" 0 ((18514.32692 1108.59729) (18523.07489 1082.20305) (18536.95136 1067.11821)))
("SF_PLANTING" 0 ((18533.18439 1127.45192) (18522.02545 1123.52602) (18514.32692 1108.59729)))
("SF_PLANTING" 0 ((18529.41176 3940.42274) (18518.09955 3940.42274)))
("SF_PLANTING" 0 ((18518.09955 3940.42274) (18521.87217 3970.58824)))
("SF_PLANTING" 0 ((18521.87217 3970.58824) (18536.94729 3981.90045) (18544.34050 3993.21267) (18544.34740 4030.92048)
(18533.33077 4061.08597) (18533.03518 4117.64706) (18529.41176 4136.50034)))
("SF_ARCHITECTURE" 0 ((18540.72398 4920.81448) (18551.88292 4935.89785) (18551.88292 4969.83382) (18544.48824
4979.94197) (18525.63914 4981.14672)))
("SF_ARCHITECTURE" 0 ((18540.72398 4920.81448) (18533.18247 4932.12670) (18533.03518 4962.29219) (18525.63914
4981.14672)))
("SF_PLANTING" 0 ((18540.72398 4155.35486) (18534.37330 4151.42907) (18529.41176 4136.50034)))
("SF_PLANTING" 0 ((18529.41176 3940.42274) (18544.49661 3910.25600)))
("SF_PLANTING" 0 ((18529.41176 3940.42274) (18567.12104 3960.32579) (18582.34943 3981.74581) (18589.74548 3985.67161)))
("SF_PLANTING" 0 ((18604.82466 935.14423) (18555.80882 934.99581) (18540.72398 931.38541) (18529.41176 935.14423)))
("SF_PLANTING" 0 ((18533.18439 976.62048) (18529.41176 935.14423)))
("SF_PLANTING" 0 ((18533.18439 1263.19853) (18533.33767 1229.26188) (18540.72398 1217.94966)))
("SF_PLANTING" 0 ((18533.18439 1263.19853) (18548.26357 1266.96833)))
("SF_PLANTING" 0 ((18533.18439 1127.45192) (18570.88801 1127.45192)))
("SF_PLANTING" 0 ((18533.18439 1127.45192) (18533.33077 1172.70079) (18540.72398 1217.94966)))
("SF_PLANTING" 0 ((18574.66063 1055.80600) (18559.57579 1065.91482) (18536.95136 1067.11821)))
("SF_PLANTING" 0 ((18536.95136 1067.11821) (18537.10747 1044.49378) (18548.26357 1025.64197)))
("SF_ARCHITECTURE" 0 ((18540.72398 4155.35486) (18540.71708 4460.78473) (18533.18247 4483.40916) (18540.72398
4920.81448)))
("SF_PLANTING" 0 ((18589.74355 4091.25147) (18567.12104 4091.40645) (18557.01154 4098.80000) (18550.83201 4147.80633)
(18540.72398 4155.35486)))
("SF_PLANTING" 0 ((18548.26357 1217.94966) (18540.72398 1217.94966)))
("SF_PLANTING" 0 ((18593.51244 3898.94378) (18544.49661 3910.25600)))
("SF_PLANTING" 0 ((18578.43326 1210.40724) (18555.81290 1210.56188) (18548.26357 1217.94966)))
("SF_PLANTING" 0 ((18555.80690 1236.80147) (18548.26357 1217.94966)))
("SF_PLANTING" 0 ((18570.88801 1029.41176) (18548.26357 1025.64197)))
("SF_PLANTING" 0 ((18634.99434 3623.68066) (18627.44502 3620.05758) (18555.80882 3616.13903)))
("SF_PLANTING" 0 ((18570.88801 1029.41176) (18577.23462 1025.48665) (18578.28405 1006.78733) (18573.46482 987.94027)
(18567.12104 980.39310)))
("SF_PLANTING" 0 ((18570.88801 1127.45192) (18574.66063 1119.90950)))
("SF_PLANTING" 0 ((18578.43326 1210.40724) (18581.00441 1180.24038) (18570.88801 1127.45192)))
("SF_PLANTING" 0 ((18570.88801 1029.41176) (18578.43326 1048.26640)))
("SF_PLANTING" 0 ((18597.28507 1119.90950) (18574.66063 1119.90950)))
("SF_PLANTING" 0 ((18574.66063 1055.80600) (18574.66063 1119.90950)))
("SF_PLANTING" 0 ((18574.66063 1055.80600) (18578.43326 1048.26640)))
("SF_PLANTING" 0 ((18638.76131 3665.15837) (18578.43326 3653.84615)))
("SF_PLANTING" 0 ((18585.97285 1048.26640) (18578.43326 1048.26640)))
("SF_ARCHITECTURE" 0 ((18589.74355 4091.25147) (18589.74355 4147.81256) (18589.74355 4166.66708) (18589.74355
4528.65803) (18589.74355 4551.28247) (18589.74355 4773.75566) (18589.74355 4788.83903) (18589.74355 4852.94118)
(18589.74355 4905.73111) (18589.74355 4920.81448) (18585.82511 5000.00000) (18582.20023 5011.31222)))
("SF_ARCHITECTURE" 0 ((18582.20023 5011.31222) (18597.28507 5018.85328)))
("SF_PLANTING" 0 ((18585.97285 1048.26640) (18601.05769 1030.60973) (18623.68213 1021.86934)))
("SF_PLANTING" 0 ((18585.97285 1048.26640) (18612.36991 1074.66063)))
("SF_PLANTING" 0 ((18589.74355 4091.25147) (18589.74355 4057.31482) (18589.74355 4042.23269) (18586.12059 4023.37817)
(18589.74548 3985.67161)))
("SF_PLANTING" 0 ((18642.53394 4004.52489) (18589.74548 3985.67161)))
("SF_PLANTING" 0 ((18638.76131 3763.19762) (18638.60803 3789.59276) (18624.88484 3808.44604) (18622.47658 3827.30057)
(18589.74548 3861.23722)))
("SF_PLANTING" 0 ((18593.51244 3898.94378) (18589.89186 3891.39649) (18589.74548 3861.23722)))
("SF_PLANTING" 0 ((18593.51244 3793.36391) (18589.74548 3815.98835)))
("SF_PLANTING" 0 ((18593.51244 3898.94378) (18631.22172 3910.25600)))
("SF_PLANTING" 0 ((18597.28507 1119.90950) (18603.62885 1112.36222) (18612.36991 1074.66063)))
("SF_PLANTING" 0 ((18597.28507 1119.90950) (18616.13688 1127.45192)))
("SF_PLANTING" 0 ((18604.82466 3733.03167) (18608.59729 3763.19762)))
("SF_PLANTING" 0 ((18604.82466 935.14423) (18619.90950 931.37919) (18638.76131 934.99581) (18702.86765 935.13733)
(18714.17986 931.37161)))
("SF_PLANTING" 0 ((18604.82466 935.14423) (18609.64672 961.53846) (18631.36946 998.19615) (18657.61878 1010.41007)
(18672.69796 1010.70554) (18695.32240 1017.95181) (18721.71946 1018.09955)))
("SF_PLANTING" 0 ((18638.76131 3763.19762) (18631.21482 3763.19762) (18608.59729 3763.19762)))
("SF_PLANTING" 0 ((18668.93100 3699.09502) (18646.30656 3692.75124) (18608.59729 3691.55396)))
("SF_PLANTING" 0 ((18631.22172 1214.17704) (18616.29299 1209.35090) (18612.36991 1199.09502)))
("SF_PLANTING" 0 ((18612.36991 1074.66063) (18642.53394 1075.71697) (18661.23937 1086.12127) (18676.47059 1104.82749)))
("SF_PLANTING" 0 ((18616.13688 1127.45192) (18623.68213 1127.45192)))
("SF_PLANTING" 0 ((18638.76131 1157.61595) (18624.73710 1149.92104) (18616.13688 1127.45192)))
("SF_PLANTING" 0 ((18627.44910 1331.07183) (18621.10532 1285.82296) (18623.68213 1266.96833)))
("SF_ARCHITECTURE" 0 ((18631.22172 5663.65011) (18633.10713 5663.65011) (18634.99242 5663.65011)))
("SF_PLANTING" 0 ((18631.22172 3951.73495) (18634.99434 3925.33937)))
("SF_PLANTING" 0 ((18695.32240 3891.40271) (18684.01018 3884.01561) (18650.07353 3888.83631) (18631.22172 3910.25600)))
("SF_PLANTING" 0 ((18634.99434 3925.33937) (18631.22172 3910.25600)))
("SF_PLANTING" 0 ((18657.61878 1304.67477) (18643.59027 1331.07183) (18641.32975 1349.77658) (18631.22172 1361.23586)))
("SF_PLANTING" 0 ((18631.22172 1214.17704) (18650.07353 1187.78281)))
("SF_PLANTING" 0 ((18646.30656 1240.57410) (18632.42590 1225.48925) (18631.22172 1214.17704)))
("SF_PLANTING" 0 ((18691.55543 3936.65158) (18634.99434 3925.33937)))
("SF_PLANTING" 0 ((18638.76131 3763.19762) (18650.07353 3763.19762) (18699.09502 3763.19762) (18721.71946 3763.19717)))
("SF_PLANTING" 0 ((18638.76131 1157.61595) (18667.73100 1134.99152) (18676.47059 1104.82749)))
("SF_PLANTING" 0 ((18638.76131 1157.61595) (18650.07353 1187.78281)))
("SF_PLANTING" 0 ((18642.53394 4004.52489) (18657.61878 3989.44152)))
("SF_PLANTING" 0 ((18642.53394 4004.52489) (18646.30656 4027.14932)))
("SF_PLANTING" 0 ((18646.30656 4027.14932) (18624.94977 4056.47964) (18642.23846 4110.10600) (18633.79434 4144.04265)
(18624.73710 4159.12477) (18624.88484 4170.43699) (18639.59265 4181.22681) (18657.61878 4151.58371)))
("SF_PLANTING" 0 ((18691.55543 4030.92048) (18684.00611 4027.29740) (18646.30656 4027.14932)))
("SF_PLANTING" 0 ((18657.61878 1304.67477) (18656.56787 1289.59276) (18646.45984 1266.96833) (18646.30656 1240.57410)))
("SF_PLANTING" 0 ((18646.30656 1240.57410) (18691.55543 1244.34389)))
("SF_PLANTING" 0 ((18695.32240 1187.78281) (18650.07353 1187.78281)))
("SF_ARCHITECTURE" 0 ((18661.38575 5663.65011) (18653.84615 5663.65011)))
("SF_PLANTING" 0 ((18783.93665 3303.16742) (18777.22421 3288.09095) (18766.96833 3280.69762) (18653.84615 3276.77251)))
("SF_PLANTING" 0 ((18695.32240 1312.21719) (18657.61878 1304.67477)))
("SF_PLANTING" 0 ((18721.71946 3834.84163) (18706.63462 3828.49785) (18676.47059 3826.25011) (18661.38575 3819.75826)))
("SF_PLANTING" 0 ((18684.01018 840.87387) (18668.93100 806.93722)))
("SF_PLANTING" 0 ((18778.28054 1097.28507) (18733.03167 1097.43281) (18676.47059 1104.82749)))
("SF_PLANTING" 0 ((18695.32240 3951.73495) (18680.24321 3959.27602)))
("SF_PLANTING" 0 ((18680.24321 3627.45057) (18699.09502 3634.99287)))
("SF_PLANTING" 0 ((18684.01018 840.87387) (18685.21018 882.35294) (18709.20305 912.51980) (18714.17986 931.37161)))
("SF_PLANTING" 0 ((18684.01018 840.87387) (18753.77262 846.52998)))
("SF_PLANTING" 0 ((18754.14819 689.29129) (18717.94683 689.89683) (18706.78518 685.21833) (18692.75124 656.10860)
(18690.35679 641.17986) (18684.01018 637.25396)))
("SF_ARCHITECTURE" 0 ((19411.76471 5663.65011) (19340.11878 5663.65011) (19325.03959 5663.65011) (18687.78281
5663.65011)))
("SF_PLANTING" 0 ((18691.55543 4030.92048) (18714.17986 4027.14932) (18736.79593 4027.29740) (18744.34389 4030.92048)))
("SF_PLANTING" 0 ((18699.09502 4110.10600) (18691.55543 4030.92048)))
("SF_PLANTING" 0 ((18695.32240 3891.40271) (18691.55543 3936.65158)))
("SF_PLANTING" 0 ((18695.32240 3951.73495) (18691.55543 3947.96380) (18691.55543 3936.65158)))
("SF_PLANTING" 0 ((18699.09502 3642.53394) (18691.55543 3650.07500)))
("SF_PLANTING" 0 ((18695.32240 1187.78281) (18698.94729 1217.94966) (18691.55543 1244.34389)))
("SF_PLANTING" 0 ((18695.32240 1312.21719) (18695.17602 1255.65611) (18691.55543 1244.34389)))
("SF_ARCHITECTURE" 0 ((18699.09502 4110.10600) (18695.33077 4121.41821) (18699.09502 4683.25792) (18699.09502
4705.88235) (18699.09502 4864.25339) (18699.09502 4917.04333) (18699.09502 4935.89785) (18699.09502 5041.47771)
(18695.32240 5067.87330)))
("SF_ARCHITECTURE" 0 ((18699.09502 5128.20554) (18702.71844 5086.72658) (18695.32240 5067.87330)))
("SF_PLANTING" 0 ((18793.36538 3940.42274) (18782.05317 3950.53020) (18736.80430 3959.12138) (18695.32240 3951.73495)))
("SF_PLANTING" 0 ((18710.40724 3891.40271) (18695.32240 3891.40271)))
("SF_ARCHITECTURE" 0 ((18695.32240 1312.21719) (18699.08812 1338.61143) (18702.86572 2217.19457) (18702.86572
2236.04853) (18699.09502 2296.38009)))
("SF_PLANTING" 0 ((18695.32240 1187.78281) (18702.87172 1184.16007) (18725.49208 1184.01301)))
("SF_ARCHITECTURE" 0 ((18748.11652 5199.84876) (18740.56719 5203.47183) (18714.17986 5203.61369) (18704.06346
5199.69480) (18699.24276 5184.76663) (18699.09502 5128.20554)))
("SF_PLANTING" 0 ((18699.09502 4110.10600) (18733.03167 4110.10600)))
("SF_PLANTING" 0 ((18699.09502 3642.53394) (18699.09502 3634.99287)))
("SF_PLANTING" 0 ((18699.09502 3642.53394) (18721.71946 3665.15837)))
("SF_PLANTING" 0 ((18717.94683 3616.13903) (18699.09502 3634.99287)))
("SF_ARCHITECTURE" 0 ((18755.65611 2349.17070) (18733.03167 2360.33439) (18717.94683 2360.33439) (18706.79072
2355.65532) (18703.02093 2349.16380) (18702.71844 2303.92805) (18699.09502 2296.38009)))
("SF_PLANTING" 0 ((18759.42873 1134.99152) (18729.25905 1143.73190) (18710.41414 1154.90249) (18702.86765 1168.92817)))
("SF_PLANTING" 0 ((18729.25905 761.68835) (18702.86765 742.83654)))
("SF_PLANTING" 0 ((18721.71946 3834.84163) (18710.40724 3891.40271)))
("SF_PLANTING" 0 ((18710.40724 3891.40271) (18717.95520 3895.02545) (18759.42873 3895.17387)))
("SF_PLANTING" 0 ((18725.49208 935.14423) (18714.17986 931.37161)))
("SF_PLANTING" 0 ((18717.94683 3616.13903) (18718.09604 3593.52081) (18721.71946 3585.97285)))
("SF_PLANTING" 0 ((18740.57127 3623.68066) (18717.94683 3616.13903)))
("SF_PLANTING" 0 ((18721.71946 3834.84163) (18748.11652 3831.07048)))
("SF_PLANTING" 0 ((18729.25905 3733.03167) (18721.71946 3763.19717)))
("SF_PLANTING" 0 ((18736.80430 3774.50939) (18721.71946 3763.19717)))
("SF_PLANTING" 0 ((18744.34389 3661.38722) (18721.71946 3665.15837)))
("SF_PLANTING" 0 ((18729.25905 3733.03167) (18721.86719 3691.55396) (18721.71946 3665.15837)))
("SF_PLANTING" 0 ((18725.49208 3567.11889) (18721.71946 3585.97285)))
("SF_PLANTING" 0 ((18759.42873 3623.68066) (18751.73020 3590.79977) (18740.57127 3586.12127) (18721.71946 3585.97285)))
("SF_PLANTING" 0 ((18721.71946 1018.09955) (18725.49208 976.62048)))
("SF_PLANTING" 0 ((18778.28054 1097.28507) (18754.59977 1055.80600) (18721.71946 1018.09955)))
("SF_PLANTING" 0 ((18754.14819 689.29129) (18721.71946 659.87839)))
("SF_PLANTING" 0 ((18725.49208 1202.86482) (18725.49208 1184.01301)))
("SF_PLANTING" 0 ((18733.03167 1184.01301) (18725.49208 1184.01301)))
("SF_PLANTING" 0 ((18763.19570 965.30826) (18744.34389 975.57172) (18725.49208 976.62048)))
("SF_PLANTING" 0 ((18725.49208 965.30826) (18725.49208 976.62048)))
("SF_PLANTING" 0 ((18725.49208 935.14423) (18725.49208 953.99604)))
("SF_PLANTING" 0 ((18725.49208 935.14423) (18763.19570 953.99604)))
("SF_PLANTING" 0 ((18755.65611 625.94174) (18725.49208 629.71437)))
("SF_PLANTING" 0 ((18729.25905 3733.03167) (18740.56719 3734.23620) (18747.05871 3740.57964) (18751.88348 3766.96833)))
("SF_PLANTING" 0 ((18729.25905 1259.42590) (18736.80837 1263.05011) (18759.42873 1263.19853)))
("SF_PLANTING" 0 ((18748.11652 757.91855) (18729.25905 761.68835)))
("SF_PLANTING" 0 ((18753.77262 846.52998) (18734.08111 791.85520) (18729.25905 761.68835)))
("SF_PLANTING" 0 ((18733.03167 4110.10600) (18744.34389 4087.48156)))
("SF_PLANTING" 0 ((18733.03167 4110.10600) (18738.00701 4132.72975) (18751.88348 4144.04265)))
("SF_PLANTING" 0 ((18736.80238 1304.67477) (18736.80238 1312.22410) (18736.80238 1331.07183) (18744.48473 1345.99921)
(18751.88348 1349.92364)))
("SF_PLANTING" 0 ((18736.80430 3774.50939) (18751.88348 3766.96833)))
("SF_PLANTING" 0 ((18736.80430 3774.50939) (18736.95068 3797.13382) (18748.11652 3831.07048)))
("SF_PLANTING" 0 ((18736.80430 3476.62115) (18748.11652 3476.62115) (18751.88348 3472.85068)))
("SF_PLANTING" 0 ((18748.11652 3438.91403) (18721.71946 3432.57647) (18711.61143 3438.92093) (18710.55498 3453.99672)
(18715.23484 3465.30271) (18721.72636 3471.79434) (18736.80430 3476.62115)))
("SF_PLANTING" 0 ((18793.36538 3540.72398) (18755.65611 3531.97817) (18744.49717 3521.87002) (18736.95068 3495.47511)
(18736.80430 3476.62115)))
("SF_PLANTING" 0 ((18736.80430 882.35294) (18744.34389 882.35294)))
("SF_PLANTING" 0 ((18751.88348 509.04977) (18736.80430 512.81957)))
("SF_PLANTING" 0 ((18755.65611 595.77771) (18745.53971 584.46550) (18736.95068 558.06844) (18736.80430 512.81957)))
("SF_PLANTING" 0 ((18740.57127 3623.68066) (18759.42873 3623.68066)))
("SF_PLANTING" 0 ((18740.57127 3623.68066) (18744.34389 3661.38722)))
("SF_PLANTING" 0 ((18740.57127 3378.58247) (18737.09842 3386.13032) (18741.77127 3401.05226) (18759.42873 3406.03371)
(18782.05317 3420.06007)))
("SF_PLANTING" 0 ((18751.88348 509.04977) (18750.83676 478.88292) (18746.92342 467.72602) (18740.57127 463.80090)))
("SF_PLANTING" 0 ((18744.34389 4087.48156) (18737.09842 4061.08597) (18744.34389 4030.92048)))
("SF_PLANTING" 0 ((18770.74095 4095.02262) (18744.34389 4087.48156)))
("SF_PLANTING" 0 ((18744.34389 4030.92048) (18819.75679 3993.21267)))
("SF_PLANTING" 0 ((18759.42873 3665.15837) (18748.11652 3665.15837) (18744.34389 3661.38722)))
("SF_PLANTING" 0 ((18759.42873 1134.99152) (18744.34389 1165.15837)))
("SF_PLANTING" 0 ((18753.77262 846.52998) (18744.34389 882.35294)))
("SF_PLANTING" 0 ((18744.34389 882.35294) (18774.50792 893.66516)))
("SF_ARCHITECTURE" 0 ((18748.11652 5199.84876) (18766.96833 5199.84876)))
("SF_ARCHITECTURE" 0 ((18755.65611 5165.91210) (18744.49717 5177.22500) (18748.11652 5199.84876)))
("SF_PLANTING" 0 ((18763.19570 3831.07048) (18748.11652 3831.07048)))
("SF_PLANTING" 0 ((18748.11652 3438.91403) (18766.96833 3437.70984) (18782.05317 3427.60181)))
("SF_PLANTING" 0 ((18748.11652 3438.91403) (18751.88348 3472.85068)))
("SF_PLANTING" 0 ((18754.14819 689.29129) (18748.11652 757.91855)))
("SF_PLANTING" 0 ((18770.74095 765.46097) (18748.11652 757.91855)))
("SF_PLANTING" 0 ((18763.19570 4140.27149) (18751.88348 4144.04265)))
("SF_ARCHITECTURE" 0 ((18755.65611 5165.91210) (18751.89186 5120.66324) (18755.64921 5090.49774) (18755.64921
4675.71686) (18751.88348 4638.00905) (18755.64921 4615.38462) (18755.65611 4306.18360) (18751.89186 4283.55916)
(18751.88348 4144.04265)))
("SF_PLANTING" 0 ((18804.67760 3759.42726) (18785.82014 3766.82025) (18751.88348 3766.96833)))
("SF_PLANTING" 0 ((18797.13235 3476.62115) (18751.88348 3472.85068)))
("SF_PLANTING" 0 ((18759.42873 1263.19853) (18766.82059 1293.36256) (18766.82059 1331.07183) (18759.28507 1345.99921)
(18751.88348 1349.92364)))
("SF_ARCHITECTURE" 0 ((18755.65611 2349.17070) (18755.64921 2251.13122) (18751.89186 2232.27726) (18751.89186
2141.77952) (18755.65611 2119.15509) (18751.89186 1968.32579) (18755.65611 1919.30645) (18751.89186 1896.68201)
(18751.88348 1349.92364)))
("SF_PLANTING" 0 ((18782.05317 509.04977) (18751.88348 509.04977)))
("SF_PLANTING" 0 ((18753.77262 846.52998) (18782.05317 852.18609)))
("SF_PLANTING" 0 ((18766.96833 625.94174) (18766.82059 667.42081) (18754.14819 689.29129)))
("SF_PLANTING" 0 ((18785.82014 701.35747) (18763.14333 696.36629) (18754.14819 689.29129)))
("SF_ARCHITECTURE" 0 ((18755.65611 5165.91210) (18765.76414 5177.22500) (18766.96833 5199.84876)))
("SF_ARCHITECTURE" 0 ((18812.21719 2352.94118) (18797.13235 2360.33439) (18778.28054 2360.33439) (18755.65611
2349.17070)))
("SF_PLANTING" 0 ((18766.96833 625.94174) (18755.65611 625.94174)))
("SF_PLANTING" 0 ((18755.65611 625.94174) (18755.65611 595.77771)))
("SF_PLANTING" 0 ((18755.65611 595.77771) (18789.59276 599.54751)))
("SF_PLANTING" 0 ((18770.74095 3880.09050) (18759.42873 3895.17387)))
("SF_PLANTING" 0 ((18793.36538 3940.42274) (18768.02466 3917.79140) (18759.42873 3895.17387)))
("SF_PLANTING" 0 ((18759.42873 3665.15837) (18778.28054 3653.84615)))
("SF_PLANTING" 0 ((18759.42873 3665.15837) (18764.25351 3680.24174) (18782.05317 3695.32387)))
("SF_PLANTING" 0 ((18759.42873 3623.68066) (18778.28054 3627.45057)))
("SF_PLANTING" 0 ((18806.56109 1210.40724) (18778.42828 1225.63767) (18759.42873 1263.19853)))
("SF_PLANTING" 0 ((18759.42873 1134.99152) (18766.97523 1133.78812) (18789.59276 1116.13971)))
("SF_PLANTING" 0 ((18763.19570 4140.27149) (18800.90498 4132.73043)))
("SF_PLANTING" 0 ((18770.74095 4095.02262) (18763.19570 4140.27149)))
("SF_PLANTING" 0 ((18763.19570 3831.07048) (18770.74502 3819.90667) (18782.05317 3813.27387) (18831.06900 3808.59446)
(18876.31787 3823.52941)))
("SF_PLANTING" 0 ((18770.74095 3880.09050) (18770.59174 3857.46606) (18763.19570 3831.07048)))
("SF_PLANTING" 0 ((18763.19570 953.99604) (18763.19570 965.30826)))
("SF_PLANTING" 0 ((18766.96833 972.85068) (18763.19570 965.30826)))
("SF_PLANTING" 0 ((18763.19570 953.99604) (18770.58484 942.68382) (18777.08473 901.21244) (18774.50792 893.66516)))
("SF_PLANTING" 0 ((18763.19570 384.61538) (18763.19570 392.15781)))
("SF_ARCHITECTURE" 0 ((18766.96833 5199.84876) (18782.05317 5203.61991) (18815.98982 5199.84876)))
("SF_PLANTING" 0 ((18766.96833 972.85068) (18770.74095 995.47511)))
("SF_PLANTING" 0 ((18766.96833 972.85068) (18785.82014 976.46719) (18804.67760 971.80124) (18827.30204 958.96584)
(18857.46606 950.22624)))
("SF_PLANTING" 0 ((18766.96833 625.94174) (18788.38857 622.01731) (18789.59276 599.54751)))
("SF_PLANTING" 0 ((18770.74095 4095.02262) (18778.28054 4095.02262)))
("SF_PLANTING" 0 ((18770.74095 3880.09050) (18796.98597 3888.68824) (18803.61980 3898.94446) (18807.55113 3917.79140)
(18815.98982 3925.33937)))
("SF_PLANTING" 0 ((18770.74095 765.46097) (18778.29016 761.83959) (18791.47624 763.57466)))
("SF_PLANTING" 0 ((18785.82014 795.62500) (18771.94367 788.07783) (18770.74095 765.46097)))
("SF_PLANTING" 0 ((18782.05317 852.18609) (18781.89706 882.35294) (18774.50792 893.66516)))
("SF_PLANTING" 0 ((18812.21719 4068.62704) (18800.90498 4069.68371) (18789.59966 4076.31719) (18778.28054 4095.02262)))
("SF_PLANTING" 0 ((18800.90498 4132.73043) (18792.30758 4110.10600) (18778.28054 4095.02262)))
("SF_PLANTING" 0 ((18778.28054 3653.84615) (18778.28054 3627.45057)))
("SF_PLANTING" 0 ((18793.36538 3672.69943) (18789.43948 3661.39412) (18778.28054 3653.84615)))
("SF_PLANTING" 0 ((18778.28054 3627.45057) (18812.21719 3623.68066)))
("SF_PLANTING" 0 ((18778.28054 1097.28507) (18789.59276 1104.82749)))
("SF_PLANTING" 0 ((18793.36538 3672.69943) (18782.05317 3695.32387)))
("SF_PLANTING" 0 ((18782.05317 3695.32387) (18787.02014 3717.94830) (18800.90498 3729.26052)))
("SF_PLANTING" 0 ((18782.05317 3427.60181) (18782.05317 3420.06007)))
("SF_PLANTING" 0 ((18782.05317 3427.60181) (18804.67760 3438.91403)))
("SF_PLANTING" 0 ((18812.21719 3408.74785) (18793.36538 3409.95204) (18782.05317 3420.06007)))
("SF_PLANTING" 0 ((18783.93665 3303.16742) (18785.67376 3318.25011) (18782.05317 3329.56233)))
("SF_PLANTING" 0 ((18782.05317 852.18609) (18797.13235 852.18609)))
("SF_PLANTING" 0 ((18782.05317 509.04977) (18789.59276 509.04977)))
("SF_PLANTING" 0 ((18782.05317 509.04977) (18789.59276 460.03111)))
("SF_PLANTING" 0 ((18783.93665 3303.16742) (18823.52941 3306.78326) (18834.84163 3299.39695)))
("SF_PLANTING" 0 ((18785.82014 795.62500) (18793.20928 784.31278) (18791.47624 763.57466)))
("SF_PLANTING" 0 ((18785.82014 795.62500) (18804.67760 822.02206)))
("SF_PLANTING" 0 ((18785.82014 701.35747) (18800.90498 693.81505)))
("SF_PLANTING" 0 ((18785.82014 701.35747) (18791.47624 763.57466)))
("SF_PLANTING" 0 ((18789.59276 3359.72851) (18800.90498 3363.49898)))
("SF_PLANTING" 0 ((18789.59276 1104.82749) (18789.59276 1116.13971)))
("SF_PLANTING" 0 ((18797.13235 1127.45192) (18789.59276 1116.13971)))
("SF_PLANTING" 0 ((18808.44457 1093.51527) (18800.89808 1094.71867) (18789.59276 1104.82749)))
("SF_PLANTING" 0 ((18789.59276 509.04977) (18789.74604 546.75622) (18796.97907 565.61086) (18789.59276 599.54751)))
("SF_PLANTING" 0 ((18898.94231 512.81957) (18861.23869 505.28484) (18789.59276 509.04977)))
("SF_PLANTING" 0 ((18791.47624 763.57466) (18853.69344 765.46097)))
("SF_PLANTING" 0 ((18793.36538 3940.42274) (18814.10068 3940.42274)))
("SF_PLANTING" 0 ((18793.36538 3672.69943) (18812.06391 3673.90419) (18818.56097 3695.32387) (18811.30860 3717.94830)
(18800.90498 3729.26052)))
("SF_PLANTING" 0 ((18793.36538 3540.72398) (18802.09525 3518.25419) (18808.44457 3514.32907)))
("SF_PLANTING" 0 ((18793.36538 3540.72398) (18812.21719 3548.26572)))
("SF_PLANTING" 0 ((18797.13235 3476.62115) (18804.67760 3438.91403)))
("SF_PLANTING" 0 ((18797.13235 3476.62115) (18808.44457 3484.16290)))
("SF_PLANTING" 0 ((18806.56109 1210.40724) (18801.05271 1195.32523) (18797.13235 1127.45192)))
("SF_PLANTING" 0 ((18797.13235 1127.45192) (18815.98982 1134.83824) (18838.61425 1134.99152)))
("SF_PLANTING" 0 ((18797.13235 852.18609) (18804.67760 822.02206)))
("SF_PLANTING" 0 ((18842.38122 878.58314) (18812.21719 866.21380) (18797.13235 852.18609)))
("SF_PLANTING" 0 ((18800.90498 4132.73043) (18804.67760 4132.73043) (18812.21719 4144.04265)))
("SF_PLANTING" 0 ((18804.67760 3759.42726) (18800.90498 3729.26052)))
("SF_PLANTING" 0 ((18800.90498 3363.49898) (18812.21719 3355.95803) (18812.21719 3352.18676)))
("SF_PLANTING" 0 ((18800.90498 3363.49898) (18815.98982 3386.12342)))
("SF_PLANTING" 0 ((18804.67760 3759.42726) (18853.68937 3759.27885) (18861.23869 3755.65611)))
("SF_PLANTING" 0 ((18812.21719 3408.74785) (18814.93201 3423.83133) (18804.67760 3438.91403)))
("SF_PLANTING" 0 ((18834.84163 3299.39695) (18808.60068 3273.00124) (18804.67760 3257.91855)))
("SF_PLANTING" 0 ((18804.67760 822.02206) (18849.92647 818.24943)))
("SF_PLANTING" 0 ((18806.56109 1210.40724) (18819.75543 1203.02014) (18857.46606 1199.09502)))
("SF_PLANTING" 0 ((18806.56109 1210.40724) (18812.06527 1221.71946) (18812.21719 1240.57410)))
("SF_PLANTING" 0 ((18808.44457 3514.32907) (18808.44457 3484.16290)))
("SF_PLANTING" 0 ((18808.44457 3514.32907) (18830.91572 3533.18224) (18834.84163 3544.49446)))
("SF_PLANTING" 0 ((18849.92647 3472.85068) (18808.44457 3484.16290)))
("SF_PLANTING" 0 ((18808.44457 1093.51527) (18811.16776 1063.34842) (18807.24876 1052.03620) (18790.80385 1033.18156)
(18790.80385 1025.64683) (18808.44457 1014.47749) (18861.23869 1014.32975)))
("SF_PLANTING" 0 ((18808.44457 1093.51527) (18838.61425 1108.59729)))
("SF_PLANTING" 0 ((18812.21719 4144.04265) (18861.23869 4144.04265)))
("SF_ARCHITECTURE" 0 ((18812.21719 4144.04265) (18812.21029 4423.07692) (18808.59378 4438.16029) (18808.45294
4498.49129) (18812.21029 4517.34581) (18812.22410 4860.48224) (18815.98145 4879.33676) (18812.22410 4901.96120)
(18812.22410 5015.08337) (18815.98145 5033.93665) (18815.98982 5199.84876)))
("SF_PLANTING" 0 ((18812.21719 4057.31482) (18812.21719 4068.62704)))
("SF_PLANTING" 0 ((18812.21719 4068.62704) (18819.91290 4083.56233) (18834.84163 4090.94898) (18845.09751 4083.70419)
(18849.92647 4068.62704)))
("SF_PLANTING" 0 ((18812.21719 4057.31482) (18827.30204 4057.16086) (18842.38122 4049.77376)))
("SF_PLANTING" 0 ((18812.21719 4057.31482) (18817.04480 4038.60962) (18831.06900 4030.92048)))
("SF_PLANTING" 0 ((18815.98982 3612.36776) (18812.21719 3623.68066)))
("SF_PLANTING" 0 ((18849.92647 3653.84615) (18823.67715 3642.38586) (18812.21719 3623.68066)))
("SF_PLANTING" 0 ((18812.21719 3548.26572) (18834.84163 3544.49446)))
("SF_PLANTING" 0 ((18812.21719 3548.26572) (18815.98982 3612.36776)))
("SF_PLANTING" 0 ((18812.21719 3408.74785) (18815.98982 3386.12342)))
("SF_ARCHITECTURE" 0 ((18812.21719 2352.94118) (18815.98145 2307.69231) (18815.98145 2179.48744) (18812.21719
2130.46731) (18815.98145 2107.84287) (18815.98982 1300.90498)))
("SF_ARCHITECTURE" 0 ((18812.21719 2352.94118) (18834.84163 2360.33518) (18861.23869 2356.71165)))
("SF_PLANTING" 0 ((18812.21719 1240.57410) (18812.36493 1289.59276) (18815.98982 1300.90498)))
("SF_PLANTING" 0 ((18863.12217 1242.45758) (18812.21719 1240.57410)))
("SF_PLANTING" 0 ((18815.98982 3925.33937) (18814.10068 3940.42274)))
("SF_PLANTING" 0 ((18814.10068 3940.42274) (18812.36912 3951.73495) (18819.75679 3993.21267)))
("SF_PLANTING" 0 ((18814.10068 3940.42274) (18872.55090 3944.19265)))
("SF_ARCHITECTURE" 0 ((18865.00566 5203.61991) (18827.30204 5203.47183) (18815.98982 5199.84876)))
("SF_PLANTING" 0 ((18846.15385 3891.40271) (18823.38857 3921.41425) (18815.98982 3925.33937)))
("SF_PLANTING" 0 ((18849.92647 3612.36776) (18815.98982 3612.36776)))
("SF_PLANTING" 0 ((18815.98982 3386.12342) (18861.23869 3382.35294)))
("SF_PLANTING" 0 ((18857.46606 1304.67477) (18815.98982 1300.90498)))
("SF_PLANTING" 0 ((18834.84163 3996.98382) (18819.75679 3993.21267)))
("SF_PLANTING" 0 ((18846.15385 678.73303) (18831.06900 679.78937) (18819.75679 686.27545)))
("SF_PLANTING" 0 ((18827.30204 3141.02590) (18823.52941 3129.71369)))
("SF_PLANTING" 0 ((18827.30204 3865.00713) (18846.15385 3891.40271)))
("SF_PLANTING" 0 ((18834.84163 3996.98382) (18831.06900 4030.92048)))
("SF_PLANTING" 0 ((18831.06900 4030.92048) (18842.38122 4034.69038)))
("SF_PLANTING" 0 ((18834.84163 3996.98382) (18853.69344 3996.98382)))
("SF_PLANTING" 0 ((18849.92647 3544.49446) (18834.84163 3544.49446)))
("SF_PLANTING" 0 ((18834.84163 3299.39695) (18846.15385 3299.39695) (18849.92647 3295.62568)))
("SF_PLANTING" 0 ((18838.61425 1134.99152) (18838.61425 1108.59729)))
("SF_PLANTING" 0 ((18838.61425 1134.99152) (18856.40973 1157.61595) (18865.00566 1176.47059)))
("SF_PLANTING" 0 ((18838.61425 1108.59729) (18849.92647 1104.97455) (18891.40271 1104.82749)))
("SF_PLANTING" 0 ((18838.61425 629.71437) (18856.26188 633.64638) (18857.46606 678.73303)))
("SF_PLANTING" 0 ((18842.38122 4049.77376) (18842.38122 4034.69038)))
("SF_PLANTING" 0 ((18842.38122 4049.77376) (18849.92647 4068.62704)))
("SF_PLANTING" 0 ((18865.00566 4023.37817) (18842.38122 4034.69038)))
("SF_PLANTING" 0 ((18842.38122 878.58314) (18849.77726 844.64649) (18849.92647 818.24943)))
("SF_PLANTING" 0 ((18842.38122 878.58314) (18851.11538 897.28167) (18857.46606 901.20758)))
("SF_PLANTING" 0 ((18898.94231 3898.94378) (18846.15385 3891.40271)))
("SF_PLANTING" 0 ((18846.15385 678.73303) (18857.46606 678.73303)))
("SF_PLANTING" 0 ((18846.15385 678.73303) (18853.54706 701.35747) (18853.69344 765.46097)))
("SF_PLANTING" 0 ((18872.55090 4068.62704) (18849.92647 4068.62704)))
("SF_PLANTING" 0 ((18849.92647 3612.36776) (18849.92647 3653.84615)))
("SF_PLANTING" 0 ((18857.46606 3657.61731) (18849.92647 3653.84615)))
("SF_PLANTING" 0 ((18849.92647 3612.36776) (18853.69344 3593.51459) (18853.54706 3555.80667) (18849.92647 3544.49446)))
("SF_PLANTING" 0 ((18849.92647 3472.85068) (18854.75124 3484.01516) (18871.34536 3495.62353) (18872.53563 3503.01686)
(18863.80984 3533.17602) (18849.92647 3544.49446)))
("SF_PLANTING" 0 ((18849.92647 3472.85068) (18850.98145 3453.99672) (18861.08948 3431.37229) (18861.23869 3382.35294)))
("SF_PLANTING" 0 ((18849.92647 3193.81572) (18850.07285 3254.14808) (18853.54016 3265.46029) (18849.92647 3295.62568)))
("SF_PLANTING" 0 ((18857.46606 3299.39695) (18849.92647 3295.62568)))
("SF_PLANTING" 0 ((18853.69344 810.70984) (18849.92647 818.24943)))
("SF_PLANTING" 0 ((18857.46606 3989.44152) (18853.69344 3996.98382)))
("SF_PLANTING" 0 ((18865.00566 4023.37817) (18853.69344 3996.98382)))
("SF_PLANTING" 0 ((18853.69344 810.70984) (18853.69344 765.46097)))
("SF_PLANTING" 0 ((18853.69344 810.70984) (18865.00566 814.33190) (18902.71493 814.47964)))
("SF_PLANTING" 0 ((18914.02715 769.23077) (18906.47919 765.60803) (18853.69344 765.46097)))
("SF_PLANTING" 0 ((18857.46606 3699.09502) (18895.17534 3697.89050) (18905.28756 3687.78281) (18910.25452 3672.69943)))
("SF_PLANTING" 0 ((18857.46606 3657.61731) (18857.46606 3699.09502)))
("SF_PLANTING" 0 ((18857.46606 3699.09502) (18861.23869 3755.65611)))
("SF_PLANTING" 0 ((18857.46606 3657.61731) (18883.86312 3657.61731)))
("SF_PLANTING" 0 ((18857.46606 3299.39695) (18854.89344 3352.18676) (18861.23869 3382.35294)))
("SF_PLANTING" 0 ((18857.46606 3299.39695) (18981.90045 3303.16742)))
("SF_PLANTING" 0 ((18863.12217 1242.45758) (18864.85928 1259.42590) (18857.46606 1304.67477)))
("SF_ARCHITECTURE" 0 ((18857.46606 1304.67477) (18861.23032 1319.75962) (18861.23869 2356.71165)))
("SF_PLANTING" 0 ((18865.00566 1176.47059) (18858.66188 1184.01787) (18857.46606 1199.09502)))
("SF_PLANTING" 0 ((18861.23869 1206.63744) (18857.46606 1206.63744) (18857.46606 1199.09502)))
("SF_PLANTING" 0 ((18861.23869 1206.63744) (18857.46606 1199.09502)))
("SF_PLANTING" 0 ((18857.46606 950.22624) (18857.46606 901.20758)))
("SF_PLANTING" 0 ((18883.86312 961.53846) (18865.01403 956.57002) (18857.46606 950.22624)))
("SF_PLANTING" 0 ((18857.46606 901.20758) (18865.01403 894.86312) (18895.17534 889.89536)))
("SF_PLANTING" 0 ((18917.79977 690.04525) (18898.94231 678.88145) (18857.46606 678.73303)))
("SF_PLANTING" 0 ((18906.48563 4166.66708) (18861.23869 4166.66708)))
("SF_PLANTING" 0 ((18861.23869 4144.04265) (18861.23869 4166.66708)))
("SF_ARCHITECTURE" 0 ((18865.00566 5203.61991) (18861.24276 5154.59989) (18861.23869 4166.66708)))
("SF_PLANTING" 0 ((18872.55090 4068.62704) (18872.40170 4113.87590) (18861.23869 4144.04265)))
("SF_PLANTING" 0 ((18891.40271 3763.19717) (18876.31787 3756.70588) (18861.23869 3755.65611)))
("SF_ARCHITECTURE" 0 ((18898.94231 2356.71165) (18883.86312 2360.48292) (18861.23869 2356.71165)))
("SF_PLANTING" 0 ((18863.12217 1242.45758) (18861.23869 1206.63744)))
("SF_PLANTING" 0 ((18861.23869 1206.63744) (18887.63009 1210.40724)))
("SF_PLANTING" 0 ((18863.12217 1242.45758) (18883.86312 1244.34389)))
("SF_ARCHITECTURE" 0 ((18865.00566 5203.61991) (18902.71493 5203.61991)))
("SF_PLANTING" 0 ((18895.17534 4023.37817) (18865.00566 4023.37817)))
("SF_PLANTING" 0 ((18891.40271 1180.24038) (18865.00566 1176.47059)))
("SF_PLANTING" 0 ((18872.55090 4068.62704) (18883.86312 4064.85713)))
("SF_PLANTING" 0 ((18902.71493 3914.02715) (18872.55090 3944.19265)))
("SF_PLANTING" 0 ((18895.17534 3963.04717) (18880.09740 3959.12138) (18872.55090 3944.19265)))
("SF_PLANTING" 0 ((18895.17534 4023.37817) (18887.77930 4038.46154) (18883.86312 4064.85713)))
("SF_PLANTING" 0 ((18883.86312 4064.85713) (18898.94231 4072.39819)))
("SF_PLANTING" 0 ((18940.42421 3604.82681) (18921.56674 3604.97455) (18902.72183 3612.52240) (18892.45905 3627.45057)
(18890.20690 3646.30441) (18883.86312 3657.61731)))
("SF_PLANTING" 0 ((18910.25452 3672.69943) (18895.17534 3667.72477) (18883.86312 3657.61731)))
("SF_PLANTING" 0 ((18883.86312 1244.34389) (18883.86312 1233.03167)))
("SF_PLANTING" 0 ((18883.86312 1244.34389) (18895.17342 1263.19853) (18895.17342 1297.13518)))
("SF_PLANTING" 0 ((18919.68326 1233.03167) (18883.86312 1233.03167)))
("SF_PLANTING" 0 ((18883.86312 1225.48925) (18883.86312 1233.03167)))
("SF_PLANTING" 0 ((18883.86312 1225.48925) (18876.31787 1229.26188) (18883.86312 1233.03167)))
("SF_PLANTING" 0 ((18883.86312 1225.48925) (18887.63009 1221.71946) (18887.63009 1210.40724)))
("SF_PLANTING" 0 ((18902.71493 953.99604) (18883.86312 961.53846)))
("SF_PLANTING" 0 ((18883.86312 961.53846) (18898.79593 1003.01753) (18898.79593 1063.34842) (18891.40271 1104.82749)))
("SF_PLANTING" 0 ((18891.40271 1180.24038) (18891.25498 1202.85995) (18887.63009 1210.40724)))
("SF_PLANTING" 0 ((18895.17534 414.78224) (18887.63009 411.00962)))
("SF_PLANTING" 0 ((18891.40271 3763.19717) (18910.25452 3745.54842) (18932.87896 3740.57274)))
("SF_PLANTING" 0 ((18891.40271 3763.19717) (18913.87387 3815.98835) (18913.87941 3872.54943) (18909.05181 3891.39649)
(18898.94231 3898.94378)))
("SF_PLANTING" 0 ((18921.56674 1180.24038) (18891.40271 1180.24038)))
("SF_PLANTING" 0 ((18891.40271 1104.82749) (18902.71493 1115.98439) (18963.04864 1116.28676) (18974.36086 1119.90950)))
("SF_PLANTING" 0 ((18923.45588 1297.13518) (18895.17342 1297.13518)))
("SF_ARCHITECTURE" 0 ((18898.94231 2356.71165) (18895.17941 2345.39943) (18898.93824 2288.83835) (18895.17342
1689.29016) (18895.17342 1670.43835) (18895.17342 1478.13066) (18895.17342 1459.27602) (18895.17342 1406.48473)
(18895.17342 1383.86029) (18895.17342 1297.13518)))
("SF_PLANTING" 0 ((18895.17534 4023.37817) (18906.48756 4023.37817)))
("SF_PLANTING" 0 ((18895.17534 3963.04717) (18896.23032 3940.42274) (18910.25452 3921.56821)))
("SF_PLANTING" 0 ((18895.17534 3963.04717) (18906.48756 4000.75373)))
("SF_PLANTING" 0 ((18895.17534 859.72851) (18895.17534 889.89536)))
("SF_PLANTING" 0 ((18930.99548 899.32127) (18895.17534 889.89536)))
("SF_PLANTING" 0 ((18895.17534 463.80090) (18906.48756 475.11312)))
("SF_PLANTING" 0 ((18898.94231 4072.39819) (18914.02715 4058.37149) (18925.33937 4053.54491)))
("SF_PLANTING" 0 ((18910.25452 4095.02262) (18898.94231 4072.39819)))
("SF_PLANTING" 0 ((18898.94231 3898.94378) (18898.94231 3910.25600) (18902.71493 3914.02715)))
("SF_ARCHITECTURE" 0 ((18898.94231 2356.71165) (18925.33937 2356.71165)))
("SF_PLANTING" 0 ((18898.94231 512.81957) (18932.87896 501.50735)))
("SF_PLANTING" 0 ((18898.94231 512.81957) (18903.91912 554.29242) (18916.74197 565.75860) (18925.19163 588.23529)
(18924.28303 599.54751) (18917.79977 610.85973)))
("SF_ARCHITECTURE" 0 ((18929.11007 5203.61991) (18902.71493 5203.61991)))
("SF_ARCHITECTURE" 0 ((18914.02715 4694.57014) (18902.86821 4709.65351) (18898.95068 4754.90238) (18902.70803
4777.52681) (18902.86267 4871.79446) (18906.47919 4886.87783) (18902.72183 4924.58563) (18902.71493 5203.61991)))
("SF_PLANTING" 0 ((18910.25452 3921.56821) (18902.71493 3914.02715)))
("SF_PLANTING" 0 ((18930.99548 899.32127) (18922.83303 908.68020) (18914.92059 938.91403) (18902.71493 953.99604)))
("SF_PLANTING" 0 ((18951.73643 969.08088) (18921.56674 964.25950) (18902.71493 953.99604)))
("SF_PLANTING" 0 ((18902.71493 814.47964) (18914.02715 769.23077)))
("SF_PLANTING" 0 ((18902.71493 814.47964) (18932.87896 833.33428)))
("SF_PLANTING" 0 ((18906.48563 4215.68586) (18917.79977 4215.68586)))
("SF_PLANTING" 0 ((18906.48563 4215.68586) (18906.48563 4166.66708)))
("SF_PLANTING" 0 ((18906.48563 4215.68586) (18906.48563 4226.99876) (18906.48563 4283.55294) (18914.02715 4291.10147)))
("SF_PLANTING" 0 ((18921.56674 4159.12477) (18906.48563 4166.66708)))
("SF_PLANTING" 0 ((18906.48756 4023.37817) (18906.48756 4000.75373)))
("SF_PLANTING" 0 ((18925.33937 4038.46154) (18906.48756 4023.37817)))
("SF_PLANTING" 0 ((18951.73643 4004.52489) (18906.48756 4000.75373)))
("SF_PLANTING" 0 ((18910.25452 4095.02262) (18932.87896 4087.48156)))
("SF_PLANTING" 0 ((18921.56674 4159.12477) (18910.40373 4117.64706) (18910.25452 4095.02262)))
("SF_PLANTING" 0 ((18955.50339 3932.88043) (18944.19118 3931.82500) (18925.33937 3922.62489) (18910.25452 3921.56821)))
("SF_PLANTING" 0 ((18944.19118 3667.04333) (18936.64468 3665.38066) (18910.25452 3672.69943)))
("SF_PLANTING" 0 ((18910.25452 607.08993) (18917.79977 610.85973)))
("SF_ARCHITECTURE" 0 ((18917.79977 4298.64253) (18914.02715 4694.57014)))
("SF_ARCHITECTURE" 0 ((18914.02715 4694.57014) (18929.11007 4705.88235) (18929.11007 5184.76663) (18929.11007
5203.61991)))
("SF_PLANTING" 0 ((18921.56674 4291.10147) (18914.02715 4291.10147)))
("SF_PLANTING" 0 ((18917.79977 4298.64253) (18914.02715 4298.64253) (18914.02715 4291.10147)))
("SF_PLANTING" 0 ((18917.79977 690.04525) (18914.17489 701.35747) (18914.17489 742.83654) (18922.93529 761.68348)
(18914.02715 769.23077)))
("SF_PLANTING" 0 ((18921.56674 4291.10147) (18917.79977 4298.64253)))
("SF_PLANTING" 0 ((18921.56674 4159.12477) (18929.11007 4166.67330) (18929.11007 4204.37364) (18917.79977 4215.68586)))
("SF_PLANTING" 0 ((18921.56674 4291.10147) (18929.11007 4283.55294) (18929.11007 4230.76923) (18917.79977 4215.68586)))
("SF_PLANTING" 0 ((18917.79977 690.04525) (18947.96380 690.04525)))
("SF_PLANTING" 0 ((18972.47172 627.82805) (18959.28020 633.33292) (18929.11606 632.27930) (18922.62455 625.93688)
(18917.79977 610.85973)))
("SF_PLANTING" 0 ((18944.19118 305.42986) (18932.87896 304.37353) (18917.79977 294.11765)))
("SF_PLANTING" 0 ((18919.68326 1233.03167) (18951.73643 1233.03167)))
("SF_PLANTING" 0 ((18919.68326 1233.03167) (18921.56674 1180.24038)))
("SF_PLANTING" 0 ((18919.68326 1233.03167) (18925.19163 1270.73812) (18923.45588 1297.13518)))
("SF_PLANTING" 0 ((18921.56674 1180.24038) (18929.11199 1180.24038)))
("SF_PLANTING" 0 ((18923.45588 1297.13518) (18955.50339 1297.13518)))
("SF_ARCHITECTURE" 0 ((18923.45588 1297.13518) (18921.56674 1715.68722) (18925.33247 1738.31165) (18925.33937
2356.71165)))
("SF_PLANTING" 0 ((18925.33937 4038.46154) (18925.33937 4053.54491)))
("SF_PLANTING" 0 ((18932.87896 4087.48156) (18925.33937 4053.54491)))
("SF_PLANTING" 0 ((18951.73643 4030.92048) (18925.33937 4038.46154)))
("SF_ARCHITECTURE" 0 ((18974.36086 2349.17070) (18951.73643 2360.33518) (18925.33937 2356.71165)))
("SF_ARCHITECTURE" 0 ((18974.36086 5196.07885) (18963.04864 5203.46527) (18929.11007 5203.61991)))
("SF_PLANTING" 0 ((18970.58824 1153.84615) (18940.57059 1158.82081) (18929.11199 1180.24038)))
("SF_PLANTING" 0 ((18955.50339 1195.32523) (18940.42421 1190.35543) (18929.11199 1180.24038)))
("SF_PLANTING" 0 ((18929.11199 354.44853) (18929.11199 361.99095)))
("SF_PLANTING" 0 ((18930.99548 899.32127) (18936.64468 878.58314) (18932.87896 833.33428)))
("SF_PLANTING" 0 ((18966.81561 904.97738) (18944.18982 904.82613) (18930.99548 899.32127)))
("SF_PLANTING" 0 ((18959.27602 4087.48156) (18932.87896 4087.48156)))
("SF_PLANTING" 0 ((18944.19118 3680.24174) (18937.84740 3687.78903) (18933.02817 3710.40724) (18932.87896 3740.57274)))
("SF_PLANTING" 0 ((18963.04864 3785.82161) (18952.79140 3778.27432) (18932.87896 3740.57274)))
("SF_PLANTING" 0 ((18932.87896 833.33428) (18978.12783 822.02206)))
("SF_PLANTING" 0 ((18932.87896 501.50735) (18932.87896 467.57070)))
("SF_PLANTING" 0 ((18963.04864 516.59219) (18932.87896 501.50735)))
("SF_PLANTING" 0 ((18936.65158 3536.95351) (18934.09276 3548.25882) (18950.53088 3563.35464) (18955.50339 3589.74333)))
("SF_PLANTING" 0 ((18955.50339 3589.74333) (18940.42421 3604.82681)))
("SF_PLANTING" 0 ((18944.19118 3667.04333) (18940.42421 3604.82681)))
("SF_PLANTING" 0 ((18940.42421 392.15781) (18951.73643 395.92760)))
("SF_PLANTING" 0 ((18944.19118 3667.04333) (18944.19118 3680.24174)))
("SF_PLANTING" 0 ((18944.19118 3680.24174) (18978.12783 3712.97364) (18996.98529 3714.17839)))
("SF_PLANTING" 0 ((18944.19118 3667.04333) (18970.58824 3668.92952)))
("SF_PLANTING" 0 ((18951.73643 297.88744) (18944.19118 305.42986)))
("SF_PLANTING" 0 ((18951.73643 395.92760) (18961.84310 388.23812) (18967.10701 365.90916) (18952.93914 350.67873)
(18951.58722 328.05430) (18944.19118 305.42986)))
("SF_PLANTING" 0 ((18947.96380 690.04525) (18970.58824 667.42081)))
("SF_PLANTING" 0 ((18947.96380 690.04525) (18959.28292 704.98020) (18983.78394 718.32579)))
("SF_PLANTING" 0 ((18951.73643 4030.92048) (18951.73643 4004.52489)))
("SF_PLANTING" 0 ((18951.73643 4030.92048) (18963.04864 4034.69038)))
("SF_PLANTING" 0 ((18951.73643 4004.52489) (18963.04864 3998.18111) (18981.90045 3996.83541) (19000.75226 3989.44152)))
("SF_PLANTING" 0 ((18963.04864 3435.14355) (18959.27602 3431.37229) (18951.73643 3435.14355)))
("SF_PLANTING" 0 ((18951.73643 1233.03167) (18959.27602 1214.17704)))
("SF_PLANTING" 0 ((18951.73643 1233.03167) (18959.42376 1244.19615) (18974.36086 1251.88631)))
("SF_PLANTING" 0 ((18951.73643 969.08088) (18966.81561 968.02376) (18978.12783 957.76867)))
("SF_PLANTING" 0 ((18951.73643 969.08088) (18956.70339 999.24491) (18970.58824 1010.55713)))
("SF_PLANTING" 0 ((18955.50339 411.00962) (18951.73643 395.92760)))
("SF_PLANTING" 0 ((18951.73643 252.63857) (18951.73643 180.99548)))
("SF_ARCHITECTURE" 0 ((19385.36765 184.76527) (19370.28846 181.00170) (18951.73643 180.99548)))
("SF_PLANTING" 0 ((18955.50339 3932.88043) (18959.42930 3925.48088) (18970.58824 3918.85373) (19019.60973 3906.63394)
(19034.68891 3906.48609)))
("SF_PLANTING" 0 ((18993.21267 3955.50486) (18966.81561 3942.99536) (18955.50339 3932.88043)))
("SF_PLANTING" 0 ((18955.50339 3589.74333) (18985.67308 3602.11199) (19000.75226 3616.13903)))
("SF_PLANTING" 0 ((19021.49321 3440.79966) (18970.59514 3401.20000) (18955.50339 3374.81120)))
("SF_PLANTING" 0 ((18955.50339 1297.13518) (18964.24446 1270.74570) (18974.36086 1263.19853)))
("SF_PLANTING" 0 ((18955.50339 1297.13518) (18974.36086 1315.98699)))
("SF_PLANTING" 0 ((18955.50339 1195.32523) (18974.36086 1172.70079)))
("SF_PLANTING" 0 ((18955.50339 1195.32523) (18959.27602 1214.17704)))
("SF_PLANTING" 0 ((18966.81561 4072.39819) (18959.27602 4087.48156)))
("SF_PLANTING" 0 ((18974.36086 4110.10600) (18960.48020 4098.79378) (18959.27602 4087.48156)))
("SF_PLANTING" 0 ((18963.04864 3785.82161) (18959.27602 3804.67613)))
("SF_PLANTING" 0 ((18981.90045 3751.88495) (18959.27602 3740.57274)))
("SF_PLANTING" 0 ((18985.67308 1214.17704) (18959.27602 1214.17704)))
("SF_PLANTING" 0 ((18959.27602 1070.89084) (18973.16086 1052.03620) (18974.36086 1036.95419)))
("SF_PLANTING" 0 ((18966.81561 4072.39819) (18963.04864 4034.69038)))
("SF_PLANTING" 0 ((18987.55656 4072.39819) (18988.23733 4042.23891) (18981.89355 4035.89514) (18963.04864 4034.69038)))
("SF_PLANTING" 0 ((18981.90045 3751.88495) (18973.30305 3781.89672) (18963.04864 3785.82161)))
("SF_PLANTING" 0 ((18963.04864 516.59219) (18970.58824 512.81957) (18970.58824 509.04977)))
("SF_PLANTING" 0 ((18974.36086 580.69287) (18967.87342 569.38066) (18960.47183 535.44400) (18963.04864 516.59219)))
("SF_PLANTING" 0 ((18966.81561 4072.39819) (18987.55656 4072.39819)))
("SF_PLANTING" 0 ((18966.81561 3887.63156) (19001.81007 3819.75826) (19020.65645 3793.51176) (19030.92195 3785.82161)))
("SF_PLANTING" 0 ((18966.81561 904.97738) (18993.21267 874.81052)))
("SF_PLANTING" 0 ((18966.81561 904.97738) (18978.12783 957.76867)))
("SF_PLANTING" 0 ((19027.14932 3657.61731) (18985.67308 3657.76516) (18974.51414 3662.43767) (18970.58824 3668.92952)))
("SF_PLANTING" 0 ((18970.58824 3668.92952) (18988.38507 3687.78281) (18996.98529 3714.17839)))
("SF_PLANTING" 0 ((18970.58824 3208.89921) (18993.36041 3246.60011) (19030.92195 3280.54299)))
("SF_PLANTING" 0 ((18970.58824 1153.84615) (18974.36086 1127.45192)))
("SF_PLANTING" 0 ((18970.58824 1153.84615) (18974.36086 1172.70079)))
("SF_PLANTING" 0 ((18970.58824 1010.55713) (18996.98529 991.70532)))
("SF_PLANTING" 0 ((18970.58824 1010.55713) (18974.36086 1036.95419)))
("SF_PLANTING" 0 ((18972.47172 627.82805) (18970.58824 667.42081)))
("SF_PLANTING" 0 ((18983.78394 718.32579) (18981.74717 682.50283) (18970.58824 667.42081)))
("SF_PLANTING" 0 ((19027.14932 505.27998) (18970.58824 509.04977)))
("SF_PLANTING" 0 ((18970.58824 467.57070) (18970.58824 509.04977)))
("SF_PLANTING" 0 ((18996.98529 441.17647) (18993.05939 460.02353) (18985.67308 466.36731) (18970.58824 467.57070)))
("SF_PLANTING" 0 ((18996.98529 441.17647) (18978.12783 434.83269) (18966.97172 438.46233) (18963.20192 448.71889)
(18970.58824 467.57070)))
("SF_PLANTING" 0 ((18972.47172 627.82805) (18970.73597 603.31731) (18974.36086 580.69287)))
("SF_PLANTING" 0 ((18972.47172 627.82805) (18985.66753 629.56312) (19023.37670 618.40215)))
("SF_ARCHITECTURE" 0 ((18974.36086 5196.07885) (18974.50724 5131.97545) (18978.12783 5113.12217) (18978.12376
5003.77115) (18974.36493 4984.91663) (18974.36086 4125.18812)))
("SF_ARCHITECTURE" 0 ((19027.14932 4125.18812) (19027.29706 4166.66708) (19030.91357 4181.74921) (19030.76584
5192.30769) (19019.60973 5203.46527) (18989.44005 5203.46527) (18974.36086 5196.07885)))
("SF_PLANTING" 0 ((19027.14932 4125.18812) (18974.36086 4125.18812)))
("SF_PLANTING" 0 ((18974.36086 4110.10600) (18974.36086 4125.18812)))
("SF_PLANTING" 0 ((18974.36086 4110.10600) (18984.46753 4102.55747) (18987.55656 4072.39819)))
("SF_PLANTING" 0 ((18974.36086 3461.53846) (18963.04864 3465.46357) (18949.16799 3480.39242) (18949.01324 3491.70464)
(18959.28292 3510.41007) (18974.36086 3520.67217) (18985.67308 3521.71538) (19008.28914 3504.22093) (19015.83710
3503.01686)))
("SF_PLANTING" 0 ((18989.44005 3152.33812) (18974.36086 3122.17195)))
("SF_ARCHITECTURE" 0 ((18974.36086 1315.98699) (18974.36493 2288.83835) (18977.83371 2303.92183) (18974.36086
2349.17070)))
("SF_ARCHITECTURE" 0 ((18974.36086 2349.17070) (18993.21267 2360.32828) (19015.83710 2360.32828) (19030.92002
2352.93428) (19030.92002 2345.39943) (19030.92002 2066.36527) (19030.92002 2039.96957) (19030.92002 2017.34514)
(19030.92002 1711.91459) (19030.92002 1696.83258) (19030.92002 1644.04129) (19030.92002 1591.25283) (19030.92002
1572.39819) (19030.92002 1463.04581) (19030.92002 1440.42138) (19030.92002 1319.75962) (19030.92002 1285.82296)))
("SF_PLANTING" 0 ((18993.21267 1278.28054) (18986.72805 1289.59276) (18985.67115 1308.43982) (18974.36086 1315.98699)))
("SF_PLANTING" 0 ((18974.36086 1251.88631) (18974.36086 1263.19853)))
("SF_PLANTING" 0 ((18993.21267 1278.28054) (18974.36086 1263.19853)))
("SF_PLANTING" 0 ((18974.36086 1251.88631) (18984.46753 1240.57410) (18985.67308 1229.26188)))
("SF_PLANTING" 0 ((18985.67308 1214.17704) (18989.28676 1184.01301) (18985.51697 1176.62523) (18974.36086 1172.70079)))
("SF_PLANTING" 0 ((18974.36086 1127.45192) (18974.36086 1119.90950)))
("SF_PLANTING" 0 ((19030.92195 1138.76414) (19008.29751 1131.36946) (18974.36086 1127.45192)))
("SF_PLANTING" 0 ((19046.00113 1067.11821) (18989.44842 1094.57093) (18974.36086 1119.90950)))
("SF_PLANTING" 0 ((18996.98529 991.70532) (19004.22251 1003.01753) (18997.87873 1025.63439) (18985.67308 1035.89706)
(18974.36086 1036.95419)))
("SF_PLANTING" 0 ((19019.60973 554.29864) (19000.90283 559.12557) (18989.29367 575.86674) (18974.36086 580.69287)))
("SF_PLANTING" 0 ((18978.12783 957.76867) (19000.75226 957.76867)))
("SF_PLANTING" 0 ((18983.78394 718.32579) (18985.52387 750.37613) (18978.27704 788.08541) (18978.12783 822.02206)))
("SF_PLANTING" 0 ((18993.21267 874.81052) (18978.12783 822.02206)))
("SF_PLANTING" 0 ((18981.90045 3751.88495) (18992.01686 3740.57274) (18996.98529 3714.17839)))
("SF_PLANTING" 0 ((19030.92195 3299.39695) (18989.44842 3299.54468) (18981.90045 3303.16742)))
("SF_PLANTING" 0 ((19051.65724 3350.30192) (19019.60973 3352.03835) (19008.29751 3347.35995) (18990.49785 3329.56233)
(18981.90045 3303.16742)))
("SF_PLANTING" 0 ((19019.60973 3073.15260) (19015.68382 3065.75238) (18996.98529 3054.15023) (18983.10464 3039.21595)
(18981.90045 3009.04977)))
("SF_PLANTING" 0 ((19030.92195 3009.04977) (19015.83710 3012.82025) (18981.90045 3009.04977)))
("SF_PLANTING" 0 ((18983.78394 718.32579) (19015.83710 720.21210)))
("SF_PLANTING" 0 ((18985.67308 1229.26188) (18985.67308 1214.17704)))
("SF_PLANTING" 0 ((18985.67308 1229.26188) (19027.14932 1233.03167)))
("SF_PLANTING" 0 ((18993.21267 297.88744) (18993.06493 324.28450) (18985.67308 346.90894)))
("SF_PLANTING" 0 ((18987.55656 4072.39819) (19030.92195 4076.16934)))
("SF_PLANTING" 0 ((19008.29751 388.38518) (18989.44005 407.23982)))
("SF_PLANTING" 0 ((19040.34502 3930.99548) (19027.15351 3943.13348) (19000.76063 3949.16143) (18993.21267 3955.50486)))
("SF_PLANTING" 0 ((18993.21267 3955.50486) (18993.36041 3970.58824) (19000.75226 3989.44152)))
("SF_PLANTING" 0 ((18993.21267 2929.86425) (19000.45124 2941.17647) (18996.98529 2952.48869)))
("SF_PLANTING" 0 ((18993.21267 1278.28054) (19030.92002 1285.82296)))
("SF_PLANTING" 0 ((19019.60973 874.81052) (18993.21267 874.81052)))
("SF_PLANTING" 0 ((19000.75226 957.76867) (18996.98529 991.70532)))
("SF_PLANTING" 0 ((18996.98529 441.17647) (19004.52489 441.17647) (19012.06448 433.63405)))
("SF_PLANTING" 0 ((19019.60973 4004.52489) (19000.75226 3989.44152)))
("SF_PLANTING" 0 ((19000.75226 957.76867) (19022.32172 942.67896) (19030.77274 920.05939) (19030.92195 901.20758)))
("SF_PLANTING" 0 ((19004.52489 2975.11312) (19027.14932 2986.42534)))
("SF_PLANTING" 0 ((19008.29751 3182.50351) (19012.22059 3193.80950) (19030.92195 3205.12794)))
("SF_PLANTING" 0 ((19021.49321 3440.79966) (19012.21369 3457.76799) (19015.83710 3503.01686)))
("SF_PLANTING" 0 ((19027.14932 3657.61731) (19030.77274 3582.20238) (19023.22342 3514.32907) (19015.83710 3503.01686)))
("SF_PLANTING" 0 ((19023.37670 618.40215) (19027.00158 625.94932) (19023.23032 697.58767) (19015.83710 720.21210)))
("SF_PLANTING" 0 ((19019.60973 874.81052) (19027.00158 840.87387) (19025.94514 731.52432) (19015.83710 720.21210)))
("SF_PLANTING" 0 ((19019.60973 4004.52489) (19030.92195 4000.76686) (19057.31335 4004.67296) (19144.04412 4030.77206)
(19162.89593 4029.71572) (19174.20814 4019.60826)))
("SF_PLANTING" 0 ((19019.60973 4004.52489) (19030.77274 4046.00260) (19030.92195 4076.16934)))
("SF_PLANTING" 0 ((19019.60973 874.81052) (19024.56980 897.28167) (19030.92195 901.20758)))
("SF_PLANTING" 0 ((19019.60973 554.29864) (19027.14932 505.27998)))
("SF_PLANTING" 0 ((19019.60973 554.29864) (19027.00158 573.15328) (19027.00158 610.85283) (19023.37670 618.40215)))
("SF_PLANTING" 0 ((19021.49321 3440.79966) (19026.92704 3431.43993) (19027.29706 3412.51912) (19039.51787 3374.81120)
(19046.14480 3363.65362) (19053.54638 3359.72851)))
("SF_PLANTING" 0 ((19021.49321 3440.79966) (19076.17081 3465.30894)))
("SF_PLANTING" 0 ((19027.14932 4125.18812) (19030.77274 4117.64084) (19030.92195 4076.16934)))
("SF_PLANTING" 0 ((19027.14932 3657.61731) (19034.68484 3699.09502) (19030.92195 3785.82161)))
("SF_PLANTING" 0 ((19027.14932 2986.42534) (19046.00113 2963.80090)))
("SF_PLANTING" 0 ((19030.92195 3009.04977) (19027.14932 2986.42534)))
("SF_PLANTING" 0 ((19030.92195 1138.76414) (19027.29706 1150.07636) (19027.14932 1233.03167)))
("SF_PLANTING" 0 ((19030.92195 1240.57410) (19027.14932 1233.03167)))
("SF_PLANTING" 0 ((19027.14932 505.27998) (19038.46154 490.19514)))
("SF_PLANTING" 0 ((19030.92195 1240.57410) (19030.92002 1274.51075) (19030.92002 1285.82296)))
("SF_PLANTING" 0 ((19049.77376 4034.69038) (19061.08597 4038.61618) (19091.10362 4068.62704) (19097.74434 4079.93925)
(19101.35260 4098.49038) (19083.71041 4097.73710) (19057.31335 4081.13710) (19030.92195 4076.16934)))
("SF_PLANTING" 0 ((19030.92195 3785.82161) (19079.93778 3783.93665)))
("SF_PLANTING" 0 ((19030.92195 3299.39695) (19030.92195 3280.54299)))
("SF_PLANTING" 0 ((19030.92195 3299.39695) (19039.51787 3333.33360) (19051.65724 3350.30192)))
("SF_PLANTING" 0 ((19038.46154 3280.54299) (19030.92195 3280.54299)))
("SF_PLANTING" 0 ((19042.23416 3197.58699) (19030.92195 3205.12794)))
("SF_PLANTING" 0 ((19046.00113 3223.98190) (19035.88756 3216.29242) (19030.92195 3205.12794)))
("SF_PLANTING" 0 ((19042.23416 3197.58699) (19030.92195 3163.65034)))
("SF_PLANTING" 0 ((19030.92195 3148.56686) (19046.00113 3114.63020)))
("SF_PLANTING" 0 ((19030.92195 3009.04977) (19042.23416 3012.82025)))
("SF_PLANTING" 0 ((19030.92195 2877.07364) (19030.92195 2846.90826)))
("SF_PLANTING" 0 ((19030.92195 1240.57410) (19076.17081 1244.34389)))
("SF_PLANTING" 0 ((19030.92195 1138.76414) (19057.31335 1138.76414)))
("SF_PLANTING" 0 ((19102.56222 754.14876) (19097.59661 784.31278) (19077.36663 810.70984) (19056.40475 882.35294)
(19049.62602 892.60882) (19030.92195 901.20758)))
("SF_PLANTING" 0 ((19034.68891 3906.48609) (19039.65735 3887.63156) (19076.17081 3842.38269)))
("SF_PLANTING" 0 ((19040.34502 3930.99548) (19034.91267 3921.63586) (19034.68891 3906.48609)))
("SF_PLANTING" 0 ((19038.46154 3280.54299) (19046.00113 3223.98190)))
("SF_PLANTING" 0 ((19038.46154 3280.54299) (19064.85860 3284.31346)))
("SF_PLANTING" 0 ((19040.34502 3930.99548) (19068.62557 3911.31267) (19121.41968 3910.25600)))
("SF_PLANTING" 0 ((19040.34502 3930.99548) (19049.77376 3944.19265)))
("SF_PLANTING" 0 ((19064.85860 3207.01357) (19042.23416 3197.58699)))
("SF_PLANTING" 0 ((19042.23416 3012.82025) (19064.85860 3009.04977)))
("SF_PLANTING" 0 ((19042.23416 3012.82025) (19042.38744 3042.98643) (19053.54638 3058.06912) (19053.54638 3065.61086)
(19053.54638 3084.46482)))
("SF_ARCHITECTURE" 0 ((19042.23416 2782.80543) (19045.70701 2771.49943) (19042.23416 2763.95147)))
("SF_PLANTING" 0 ((19064.85860 3207.01357) (19057.16697 3219.15158) (19046.00113 3223.98190)))
("SF_PLANTING" 0 ((19053.54638 3084.46482) (19060.92443 3099.54751) (19057.16007 3107.08235) (19046.00113 3114.63020)))
("SF_PLANTING" 0 ((19053.54638 3084.46482) (19042.38744 3089.43326) (19038.61482 3095.78326) (19039.65735 3110.70509)
(19046.00113 3114.63020)))
("SF_PLANTING" 0 ((19046.00113 2941.17647) (19042.38744 2948.72443) (19046.00113 2963.80090)))
("SF_PLANTING" 0 ((19064.85860 3009.04977) (19063.80079 2978.88360) (19057.16697 2967.72602) (19046.00113 2963.80090)))
("SF_PLANTING" 0 ((19046.00113 2892.15713) (19053.54638 2918.55204)))
("SF_PLANTING" 0 ((19049.77376 1048.26640) (19046.00113 1067.11821)))
("SF_PLANTING" 0 ((19072.39819 1070.89084) (19046.00113 1067.11821)))
("SF_PLANTING" 0 ((19049.77376 3944.19265) (19057.46391 3963.04717) (19079.93778 3981.90045)))
("SF_PLANTING" 0 ((19127.07579 3942.30769) (19110.10747 3947.95758) (19049.77376 3944.19265)))
("SF_PLANTING" 0 ((19108.21833 1014.32975) (19079.94615 1022.92647) (19049.77376 1048.26640)))
("SF_PLANTING" 0 ((19049.77376 1048.26640) (19046.15034 1044.34050) (19047.20113 1025.64197) (19078.73507 980.39310)
(19079.93778 953.99604)))
("SF_PLANTING" 0 ((19051.65724 3350.30192) (19068.62557 3337.10407)))
("SF_PLANTING" 0 ((19051.65724 3350.30192) (19053.54638 3359.72851)))
("SF_PLANTING" 0 ((19087.48303 3397.43563) (19076.02025 3374.95973) (19053.54638 3359.72851)))
("SF_PLANTING" 0 ((19064.85860 3207.01357) (19061.08597 3193.81572)))
("SF_PLANTING" 0 ((19061.08597 2820.51256) (19061.08597 2858.22048)))
("SF_PLANTING" 0 ((19400.45249 2812.97161) (19355.20362 2813.11934) (19340.11878 2816.73586) (19072.39819 2816.74830)
(19061.08597 2820.51256)))
("SF_PLANTING" 0 ((19079.93778 3208.89921) (19086.28439 3242.83586) (19082.51459 3257.91855) (19064.85860 3284.31346)))
("SF_PLANTING" 0 ((19064.85860 3284.31346) (19072.25045 3306.93790) (19068.62557 3337.10407)))
("SF_PLANTING" 0 ((19064.85860 3207.01357) (19079.93778 3208.89921)))
("SF_PLANTING" 0 ((19064.85860 3156.10860) (19066.06131 3166.90441) (19091.10362 3158.68122) (19110.10747 3129.71369)))
("SF_PLANTING" 0 ((19064.85860 3009.04977) (19106.33484 3012.82025)))
("SF_PLANTING" 0 ((19110.10747 3340.87455) (19068.62557 3337.10407)))
("SF_PLANTING" 0 ((19072.39819 1070.89084) (19095.02262 1056.86312) (19106.33484 1055.80600)))
("SF_PLANTING" 0 ((19130.84276 1059.57862) (19121.26357 1085.81821) (19102.56222 1093.36686) (19083.71731 1092.31041)
(19077.22579 1085.96595) (19072.39819 1070.89084)))
("SF_PLANTING" 0 ((19132.73190 3842.38269) (19076.17081 3842.38269)))
("SF_PLANTING" 0 ((19076.17081 3842.38269) (19079.93778 3783.93665)))
("SF_PLANTING" 0 ((19083.71041 3465.30894) (19076.17081 3465.30894)))
("SF_PLANTING" 0 ((19076.17081 3465.30894) (19073.59400 3480.39242) (19087.48303 3589.74333)))
("SF_ARCHITECTURE" 0 ((19332.57919 4800.15124) (19306.18213 4803.92115) (19287.33032 4800.30520) (19249.62104
4803.92115) (19226.99661 4800.15747) (19091.25000 4800.15747) (19079.93778 4803.92115)))
("SF_PLANTING" 0 ((19132.73190 3729.26052) (19120.52342 3744.34389) (19113.72115 3766.96210) (19079.93778 3783.93665)))
("SF_PLANTING" 0 ((19087.48303 3589.74333) (19079.93778 3783.93665)))
("SF_PLANTING" 0 ((19079.93778 3208.89921) (19091.10362 3203.93009) (19098.79525 3193.81572)))
("SF_PLANTING" 0 ((19102.56222 2914.78156) (19079.93778 2937.40600)))
("SF_ARCHITECTURE" 0 ((19079.93778 2055.05283) (19098.79525 2055.05283) (19332.57919 2055.05283)))
("SF_ARCHITECTURE" 0 ((19079.93778 2021.11640) (19106.33484 2024.88688) (19313.72738 2024.88066) (19328.80656
2021.11640)))
("SF_PLANTING" 0 ((19144.04412 942.68382) (19162.59355 916.28959) (19151.57681 898.78824) (19129.10701 905.13201)
(19117.49932 923.83201) (19098.79525 942.67896) (19079.93778 953.99604)))
("SF_PLANTING" 0 ((19121.41968 822.02206) (19111.31018 837.10407) (19101.50724 878.58314) (19077.22579 931.37161)
(19079.93778 953.99604)))
("SF_PLANTING" 0 ((19079.93778 671.19061) (19083.71041 674.96324) (19095.02262 674.96324)))
("SF_PLANTING" 0 ((19079.93778 637.25396) (19098.79525 652.33880)))
("SF_ARCHITECTURE" 0 ((19083.71041 4837.85781) (19325.03959 4837.85781)))
("SF_PLANTING" 0 ((19083.71041 3465.30894) (19087.33382 3453.99672) (19087.48303 3397.43563)))
("SF_PLANTING" 0 ((19083.71041 3465.30894) (19110.09910 3473.00532) (19132.73190 3501.81267) (19151.58371 3502.86833)
(19166.66855 3495.47511)))
("SF_PLANTING" 0 ((19106.33484 3012.82025) (19105.13903 3042.98643) (19083.71041 3073.15260)))
("SF_ARCHITECTURE" 0 ((19083.71041 1659.12613) (19291.10294 1659.13100) (19313.72738 1662.89593) (19332.57919
1659.12613)))
("SF_ARCHITECTURE" 0 ((19087.48303 4441.93020) (19325.03959 4441.93020)))
("SF_PLANTING" 0 ((19087.48303 3589.74333) (19108.90192 3578.28337) (19114.02364 3540.72398) (19121.41968 3525.64129)))
("SF_PLANTING" 0 ((19087.48303 3397.43563) (19132.73190 3412.51912)))
("SF_ARCHITECTURE" 0 ((19321.26697 4475.86686) (19102.56222 4475.86063) (19091.25000 4472.09695)))
("SF_ARCHITECTURE" 0 ((19332.57919 1632.72907) (19313.72738 1625.19434) (19159.12330 1625.19434) (19110.10747
1628.95928) (19095.02262 1625.18948)))
("SF_PLANTING" 0 ((19095.02262 674.96324) (19098.79525 652.33880)))
("SF_PLANTING" 0 ((19095.02262 674.96324) (19097.59525 682.51041) (19093.97319 693.81505) (19066.06131 727.75170)
(19065.01188 742.83654) (19072.40509 752.94389) (19102.56222 754.14876)))
("SF_ARCHITECTURE" 0 ((19328.80656 2752.63925) (19098.79525 2752.63925)))
("SF_PLANTING" 0 ((19113.87443 584.46550) (19110.26075 599.54751) (19111.62229 641.02658) (19098.79525 652.33880)))
("SF_PLANTING" 0 ((19110.10747 727.75170) (19112.52262 739.06391) (19102.56222 754.14876)))
("SF_PLANTING" 0 ((19106.33484 3012.82025) (19113.87443 3009.04977)))
("SF_PLANTING" 0 ((19108.21833 1014.32975) (19106.33484 1055.80600)))
("SF_PLANTING" 0 ((19130.84276 1059.57862) (19106.33484 1055.80600)))
("SF_PLANTING" 0 ((19108.21833 1014.32975) (19117.64706 1014.32975)))
("SF_PLANTING" 0 ((19108.21833 1014.32975) (19106.48676 1003.01753) (19111.30328 987.93269) (19132.73190 953.99604)))
("SF_PLANTING" 0 ((19110.10747 3340.87455) (19128.95928 3335.90611) (19177.98077 3304.36538) (19204.21889 3296.97828)
(19207.84242 3303.17432) (19203.16946 3322.02138) (19193.05995 3333.33360)))
("SF_PLANTING" 0 ((19110.10747 3340.87455) (19110.25385 3322.02138) (19117.64706 3299.39695)))
("SF_PLANTING" 0 ((19113.87443 3009.04977) (19117.64706 2982.65486)))
("SF_PLANTING" 0 ((19377.82805 3012.82025) (19362.74321 3009.05600) (19113.87443 3009.04977)))
("SF_PLANTING" 0 ((19140.27149 3857.46606) (19121.41968 3910.25600)))
("SF_PLANTING" 0 ((19127.07579 3942.30769) (19121.63925 3932.94808) (19121.41968 3910.25600)))
("SF_PLANTING" 0 ((19127.07579 3942.30769) (19140.26731 3936.80283) (19177.98077 3932.89355) (19200.60520 3944.19265)))
("SF_PLANTING" 0 ((19127.07579 3942.30769) (19133.92771 3962.89219) (19140.27149 3966.81708)))
("SF_PLANTING" 0 ((19128.95928 3435.14355) (19132.73190 3412.51912)))
("SF_PLANTING" 0 ((19130.84276 1059.57862) (19170.43552 1055.65894) (19193.05995 1047.20928) (19226.99661 1006.78733)))
("SF_PLANTING" 0 ((19130.84276 1059.57862) (19147.81109 1040.72398)))
("SF_PLANTING" 0 ((19132.73190 3842.38269) (19141.46731 3812.21719) (19170.28224 3778.28054) (19169.38054 3763.19717)
(19159.12330 3733.03167)))
("SF_PLANTING" 0 ((19132.73190 3842.38269) (19140.27149 3857.46606)))
("SF_PLANTING" 0 ((19132.73190 3729.26052) (19151.58371 3729.26052)))
("SF_PLANTING" 0 ((19132.73190 3729.26052) (19126.38529 3721.71324) (19122.46640 3706.63609) (19121.56606 3684.01165)
(19130.00871 3646.30509) (19144.04412 3619.90950)))
("SF_PLANTING" 0 ((19132.73190 3412.51912) (19140.27149 3408.74785)))
("SF_PLANTING" 0 ((19144.04412 3205.12794) (19136.49887 3223.98190)))
("SF_PLANTING" 0 ((19200.60520 3944.19265) (19193.05588 3954.30758) (19162.89593 3965.76165) (19140.27149 3966.81708)))
("SF_PLANTING" 0 ((19140.27149 3966.81708) (19141.47568 3989.44152) (19162.88903 4004.67952) (19174.20814 4019.60826)))
("SF_PLANTING" 0 ((19140.27149 3857.46606) (19162.89593 3857.46606)))
("SF_PLANTING" 0 ((19144.04412 3619.90950) (19155.35633 3616.13903)))
("SF_PLANTING" 0 ((19174.20814 3495.47511) (19165.61765 3536.95351) (19148.86199 3567.11889) (19137.70441 3608.59729)
(19144.04412 3619.90950)))
("SF_PLANTING" 0 ((19204.37217 3559.57794) (19182.95328 3601.05554) (19188.08744 3619.90950) (19171.63552 3646.30509)
(19165.61765 3702.86618) (19151.58371 3729.26052)))
("SF_PLANTING" 0 ((19159.12330 3733.03167) (19151.58371 3729.26052)))
("SF_PLANTING" 0 ((19159.12330 3733.03167) (19185.52036 3730.15600) (19196.68484 3721.71324) (19215.68439 3696.52862)
(19234.54186 3695.32387)))
("SF_PLANTING" 0 ((19162.89593 3857.46606) (19170.44389 3846.30848) (19184.47093 3838.45781) (19224.27636 3774.51007)
(19249.46776 3751.88495) (19257.16629 3736.80283)))
("SF_PLANTING" 0 ((19162.89593 3857.46606) (19170.44389 3863.80984) (19204.37217 3868.93292) (19215.68439 3876.31934)))
("SF_PLANTING" 0 ((19215.68439 3876.31934) (19204.36810 3895.02545) (19166.66855 3914.02715)))
("SF_PLANTING" 0 ((19174.20814 3495.47511) (19166.66855 3495.47511)))
("SF_PLANTING" 0 ((19189.29299 3378.58247) (19195.63676 3382.50758) (19196.67930 3393.66516) (19186.72455 3408.74785)
(19176.92986 3442.68450) (19167.86437 3457.76799) (19163.04921 3484.16290) (19166.66855 3495.47511)))
("SF_PLANTING" 0 ((19166.66855 3144.79638) (19166.66855 3152.33812)))
("SF_PLANTING" 0 ((19181.74774 4023.37817) (19174.20814 4019.60826)))
("SF_PLANTING" 0 ((19174.20814 3495.47511) (19193.05995 3484.16290)))
("SF_PLANTING" 0 ((19219.45701 599.54751) (19185.67364 600.75238) (19181.74774 614.62952)))
("SF_PLANTING" 0 ((19200.60520 3944.19265) (19215.68439 3944.19265)))
("SF_PLANTING" 0 ((19211.91742 3751.88495) (19233.33631 3717.94830) (19234.54186 3695.32387)))
("SF_PLANTING" 0 ((19245.85407 3401.20690) (19235.59683 3408.75475) (19211.91742 3446.45577)))
("SF_PLANTING" 0 ((19223.22964 3231.52364) (19211.91742 3239.06459)))
("SF_PLANTING" 0 ((19268.47851 3857.46606) (19238.30882 3871.49310) (19215.68439 3876.31934)))
("SF_PLANTING" 0 ((19242.08145 3601.05554) (19244.65407 3612.36776) (19240.89118 3623.68066) (19230.62149 3638.76278)
(19215.68439 3650.07500)))
("SF_PLANTING" 0 ((19219.45701 957.76867) (19220.66120 942.83914) (19227.00498 939.06867) (19313.72738 938.92025)
(19340.11878 942.68382)))
("SF_PLANTING" 0 ((19219.45701 614.62952) (19219.45701 599.54751)))
("SF_PLANTING" 0 ((19328.80656 595.77771) (19287.33032 603.31244) (19219.45701 599.54751)))
("SF_PLANTING" 0 ((19238.30882 3684.01165) (19234.54186 3695.32387)))
("SF_PLANTING" 0 ((19264.70588 3717.94830) (19257.16629 3736.80283)))
("SF_PLANTING" 0 ((19287.33032 3740.57274) (19257.16629 3736.80283)))
("SF_PLANTING" 0 ((19272.24548 1014.32975) (19317.49434 1014.18133) (19328.80656 1010.55713)))
("SF_PLANTING" 0 ((19317.49434 3431.37229) (19294.86991 3427.60181)))
("SF_PLANTING" 0 ((19336.35181 3766.96833) (19313.72738 3748.11505)))
("SF_PLANTING" 0 ((19325.03959 3838.61278) (19321.26697 3846.15385)))
("SF_ARCHITECTURE" 0 ((19377.82805 3012.82025) (19374.05543 3065.61086) (19374.20464 3114.63020) (19377.82115
3129.71369) (19377.83495 3574.66063) (19381.60068 3597.28507) (19381.59231 3808.44604) (19377.83495 3827.30057)
(19381.60068 4826.54559) (19377.82805 4849.17002) (19377.82805 5610.85973)))
("SF_ARCHITECTURE" 0 ((19377.82805 5610.85973) (19441.92873 5611.01437) (19449.46561 5614.78484) (19456.86029
5625.94276) (19457.16131 5652.33778) (19464.55317 5682.50385)))
("SF_ARCHITECTURE" 0 ((19377.82805 3012.82025) (19389.14027 3009.19751) (19426.84955 3008.89514) (19438.00566
2997.73756) (19434.39604 2963.80090) (19434.23586 2820.51946) (19426.84118 2813.12624) (19400.45249 2812.97161)))
("SF_ARCHITECTURE" 0 ((19381.60068 2967.57138) (19385.22127 2960.02353) (19385.36765 2880.84491)))
("SF_ARCHITECTURE" 0 ((19385.36765 5874.81154) (19419.30430 5869.99095) (19487.17760 5847.36652) (19501.20611
5837.09751) (19506.03507 5822.02104)))
("SF_ARCHITECTURE" 0 ((19396.67986 6489.44186) (19389.28801 6455.50520) (19389.14027 6327.30023) (19389.14027
6308.44638) (19385.36765 5874.81154)))
("SF_ARCHITECTURE" 0 ((19430.61652 -3.77070) (19426.85362 15.08201) (19426.69344 165.91346) (19422.92364 173.30600)
(19411.76471 179.93914) (19385.36765 184.76527)))
("SF_ARCHITECTURE" 0 ((19400.45249 2812.97161) (19399.40305 2771.49321) (19392.75679 2756.41674) (19379.03224
2744.94977) (19381.59876 2070.13575) (19385.36357 2055.05283) (19385.37602 629.71437) (19389.14027 607.08993)
(19385.37602 584.46550) (19385.22127 478.88292) (19381.60475 463.80090) (19381.60475 199.85011) (19385.36765
184.76527)))
("SF_ARCHITECTURE" 0 ((19430.61652 -3.77070) (20000.00000 0.00000)))
("SF_ARCHITECTURE" 0 ((19457.01357 5690.04525) (19464.55317 5682.50385)))
("SF_ARCHITECTURE" 0 ((19521.11425 5742.83552) (19498.34344 5697.73473) (19464.55317 5682.50385)))
("SF_ARCHITECTURE" 0 ((19506.03507 5822.02104) (19551.28394 5818.10238) (19585.22059 5810.55407) (19596.37670
5799.39661) (19596.37670 5769.23733) (19592.60690 5762.74581) (19555.05090 5752.95667) (19539.97172 5743.89186)
(19521.11425 5742.83552)))
("SF_PLANTING" 1 ((837.10407 3173.07692) (838.98948 3174.96233) (840.87477 3173.07692) (838.98948 3171.19152)))
("SF_PLANTING" 1 ((847.21199 3256.71437) (833.33326 3257.77014) (822.02771 3253.09163) (815.67749 3246.60011) (814.78235
3231.67828) (822.02127 3227.90701) (840.72014 3228.95656) (848.26821 3246.60633)))
("SF_PLANTING" 1 ((1059.58428 394.72274) (1070.88982 394.72274) (1080.99774 384.61538) (1082.04740 369.53824)
(1078.27670 363.34423) (1059.58428 370.58903) (1053.24061 377.08054) (1053.24061 388.38032)))
("SF_PLANTING" 1 ((1193.43891 3152.33790) (1195.32432 3154.22319) (1197.20962 3152.33790) (1195.32432 3150.45249)))
("SF_PLANTING" 1 ((1255.65611 4083.71041) (1257.54152 4085.59581) (1259.42681 4083.71041) (1257.54152 4081.82500)))
("SF_PLANTING" 1 ((1410.25645 1338.61233) (1412.14174 1340.49774) (1414.02715 1338.61233) (1412.14174 1336.72704)))
("SF_PLANTING" 1 ((1809.95475 3503.01663) (1811.84016 3504.90192) (1813.72545 3503.01663) (1811.84016 3501.13122)))
("SF_PLANTING" 1 ((1811.84016 3563.34842) (1813.72545 3565.23382) (1815.61086 3563.34842) (1813.72545 3561.46301)))
("SF_ARCHITECTURE" 1 ((1849.54751 5101.80995) (1851.43292 5103.69536) (1853.31821 5101.80995) (1851.43292 5099.92455)))
("SF_PLANTING" 1 ((1900.45249 3563.34842) (1902.33790 3565.23382) (1904.22319 3563.34842) (1902.33790 3561.46301)))
("SF_PLANTING" 1 ((1900.45249 3503.01663) (1902.33790 3504.90192) (1904.22319 3503.01663) (1902.33790 3501.13122)))
("SF_PLANTING" 1 ((1943.81595 3653.84615) (1945.70136 3655.73156) (1947.58676 3653.84615) (1945.70136 3651.96075)))
("SF_PLANTING" 1 ((2264.32885 465.68631) (2266.21414 467.57161) (2268.09955 465.68631) (2266.21414 463.80090)))
("SF_PLANTING" 1 ((2411.38767 3729.26097) (2413.27296 3731.14627) (2415.15837 3729.26097) (2413.27296 3727.37557)))
("SF_PLANTING" 1 ((2467.94876 1001.13122) (2469.83405 1003.01663) (2471.71946 1001.13122) (2469.83405 999.24581)))
("SF_PLANTING" 1 ((2547.13428 1266.96833) (2549.01957 1268.85373) (2550.90498 1266.96833) (2549.01957 1265.08292)))
("SF_ARCHITECTURE" 1 ((2718.70283 5667.42081) (2720.58824 5669.30622) (2722.47364 5667.42081) (2720.58824 5665.53541)))
("SF_ARCHITECTURE" 1 ((2735.67115 2058.82353) (2737.55656 2060.70894) (2739.44197 2058.82353) (2737.55656 2056.93812)))
("SF_ARCHITECTURE" 1 ((2735.67115 2021.11618) (2737.55656 2023.00147) (2739.44197 2021.11618) (2737.55656 2019.23077)))
("SF_ARCHITECTURE" 1 ((2737.55656 4837.85826) (2739.44197 4839.74355) (2741.32726 4837.85826) (2739.44197 4835.97285)))
("SF_ARCHITECTURE" 1 ((2739.44197 1694.94717) (2741.32726 1696.83258) (2743.21267 1694.94717) (2741.32726 1693.06188)))
("SF_PLANTING" 1 ((2771.49321 7009.80396) (2773.37862 7011.68925) (2775.26391 7009.80396) (2773.37862 7007.91855)))
("SF_MASONRY_AND_ARCH" 1 ((3031.67421 3476.62138) (3033.55962 3478.50679) (3035.44491 3476.62138) (3033.55962
3474.73609)))
("SF_MASONRY_AND_ARCH" 1 ((3124.05735 1747.73756) (3125.94265 1749.62296) (3127.82805 1747.73756) (3125.94265
1745.85215)))
("SF_PLANTING" 1 ((3129.71346 6397.05882) (3131.59876 6398.94423) (3133.48416 6397.05882) (3131.59876 6395.17342)))
("SF_PLANTING" 1 ((3135.36957 6623.30317) (3137.25486 6625.18857) (3139.14027 6623.30317) (3137.25486 6621.41776)))
("SF_MASONRY_AND_ARCH" 1 ((3144.79638 1725.11312) (3146.68179 1726.99853) (3148.56708 1725.11312) (3146.68179
1723.22771)))
("SF_ARCHITECTURE" 1 ((3233.40871 5759.80396) (3235.29412 5761.68925) (3237.17952 5759.80396) (3235.29412 5757.91855)))
("SF_MASONRY_AND_ARCH" 1 ((3248.49174 2545.24887) (3250.37704 2547.13428) (3252.26244 2545.24887) (3250.37704
2543.36346)))
("SF_MASONRY_AND_ARCH" 1 ((3259.80396 1131.22172) (3261.68925 1133.10713) (3263.57466 1131.22172) (3261.68925
1129.33631)))
("SF_PLANTING" 1 ((3271.11618 746.60633) (3273.00147 748.49174) (3274.88688 746.60633) (3273.00147 744.72093)))
("SF_MASONRY_AND_ARCH" 1 ((3295.62590 1035.06787) (3297.51131 1036.95328) (3299.39672 1035.06787) (3297.51131
1033.18247)))
("SF_MASONRY_AND_ARCH" 1 ((3346.53088 3371.04072) (3348.41629 3372.92613) (3350.30170 3371.04072) (3348.41629
3369.15532)))
("SF_MASONRY_AND_ARCH" 1 ((3467.19457 3536.95328) (3469.07998 3538.83857) (3470.96527 3536.95328) (3469.07998
3535.06787)))
("SF_MASONRY_AND_ARCH" 1 ((3470.96527 1361.23676) (3472.85068 1363.12217) (3474.73609 1361.23676) (3472.85068
1359.35147)))
("SF_MASONRY_AND_ARCH" 1 ((3589.74355 3340.87477) (3591.62896 3342.76018) (3593.51437 3340.87477) (3591.62896
3338.98948)))
("SF_MASONRY_AND_ARCH" 1 ((3670.81448 935.14333) (3672.69989 937.02862) (3674.58518 935.14333) (3672.69989 933.25792)))
("SF_MASONRY_AND_ARCH" 1 ((3791.47817 1768.47658) (3793.36346 1770.36199) (3795.24887 1768.47658) (3793.36346
1766.59129)))
("SF_ARCHITECTURE" 1 ((3800.90498 5757.91855) (3802.79038 5759.80396) (3804.67568 5757.91855) (3802.79038 5756.03314)))
("SF_MASONRY_AND_ARCH" 1 ((3800.90498 2145.55057) (3802.79038 2147.43586) (3804.67568 2145.55057) (3802.79038
2143.66516)))
("SF_MASONRY_AND_ARCH" 1 ((3800.90498 1874.05735) (3802.79038 1875.94265) (3804.67568 1874.05735) (3802.79038
1872.17195)))
("SF_MASONRY_AND_ARCH" 1 ((3808.44649 3289.96980) (3810.33179 3291.85520) (3812.21719 3289.96980) (3810.33179
3288.08450)))
("SF_MASONRY_AND_ARCH" 1 ((3889.51731 953.99695) (3891.40271 955.88235) (3893.28812 953.99695) (3891.40271 952.11165)))
("SF_MASONRY_AND_ARCH" 1 ((3893.28812 1561.08597) (3895.17342 1562.97138) (3897.05882 1561.08597) (3895.17342
1559.20057)))
("SF_MASONRY_AND_ARCH" 1 ((3932.88088 3148.56708) (3934.76618 3150.45249) (3936.65158 3148.56708) (3934.76618
3146.68179)))
("SF_MASONRY_AND_ARCH" 1 ((3972.47364 2927.97885) (3974.35894 2929.86425) (3976.24434 2927.97885) (3974.35894
2926.09355)))
("SF_MASONRY_AND_ARCH" 1 ((3974.35894 2475.49016) (3976.24434 2477.37557) (3978.12975 2475.49016) (3976.24434
2473.60486)))
("SF_MASONRY_AND_ARCH" 1 ((3980.01505 1136.87783) (3981.90045 1138.76324) (3983.78586 1136.87783) (3981.90045
1134.99242)))
("SF_MASONRY_AND_ARCH" 1 ((3981.90045 1466.81753) (3983.78586 1468.70283) (3985.67115 1466.81753) (3983.78586
1464.93213)))
("SF_MASONRY_AND_ARCH" 1 ((4002.63948 2820.51278) (4004.52489 2822.39819) (4006.41029 2820.51278) (4004.52489
2818.62749)))
("SF_MASONRY_AND_ARCH" 1 ((4047.88835 1655.35441) (4049.77376 1657.23982) (4051.65916 1655.35441) (4049.77376
1653.46912)))
("SF_MASONRY_AND_ARCH" 1 ((4059.20057 2151.20667) (4061.08597 2153.09197) (4062.97138 2151.20667) (4061.08597
2149.32127)))
("SF_PLANTING" 1 ((4061.08597 345.02262) (4062.97138 346.90803) (4064.85667 345.02262) (4062.97138 343.13722)))
("SF_MASONRY_AND_ARCH" 1 ((4093.13722 2266.21414) (4095.02262 2268.09955) (4096.90803 2266.21414) (4095.02262
2264.32885)))
("SF_MASONRY_AND_ARCH" 1 ((4119.53247 1894.79638) (4121.41776 1896.68179) (4123.30317 1894.79638) (4121.41776
1892.91097)))
("SF_MASONRY_AND_ARCH" 1 ((4132.72998 1817.49627) (4134.61538 1819.38156) (4136.50079 1817.49627) (4134.61538
1815.61086)))
("SF_PLANTING" 1 ((4155.35441 6977.75260) (4157.23982 6979.63801) (4159.12523 6977.75260) (4157.23982 6975.86731)))
("SF_MASONRY_AND_ARCH" 1 ((4155.35441 2658.37104) (4157.23982 2660.25645) (4159.12523 2658.37104) (4157.23982
2656.48563)))
("SF_SOLAR" 1 ((4157.23982 8180.61844) (4159.12523 8182.50373) (4161.01052 8180.61844) (4159.12523 8178.73303)))
("SF_PLANTING" 1 ((4159.12523 723.98190) (4161.01052 725.86731) (4162.89593 723.98190) (4161.01052 722.09649)))
("SF_SOLAR" 1 ((4168.55204 8157.99400) (4170.43744 8159.87930) (4172.32274 8157.99400) (4170.43744 8156.10860)))
("SF_SOLAR" 1 ((4183.63495 8144.79638) (4185.52036 8146.68179) (4187.40577 8144.79638) (4185.52036 8142.91097)))
("SF_SOLAR" 1 ((4194.94717 8174.96233) (4196.83258 8176.84762) (4198.71799 8174.96233) (4196.83258 8173.07692)))
("SF_SOLAR" 1 ((4194.94717 8129.71346) (4196.83258 8131.59876) (4198.71799 8129.71346) (4196.83258 8127.82805)))
("SF_SOLAR" 1 ((4202.48869 8110.85973) (4204.37410 8112.74514) (4206.25939 8110.85973) (4204.37410 8108.97432)))
("SF_SOLAR" 1 ((4213.80090 8190.04525) (4215.68631 8191.93066) (4217.57161 8190.04525) (4215.68631 8188.15984)))
("SF_SOLAR" 1 ((4213.80090 8142.91097) (4215.68631 8144.79638) (4217.57161 8142.91097) (4215.68631 8141.02568)))
("SF_MASONRY_AND_ARCH" 1 ((4215.68631 2477.37557) (4217.57161 2479.26097) (4219.45701 2477.37557) (4217.57161
2475.49016)))
("SF_SOLAR" 1 ((4217.57161 8095.77681) (4219.45701 8097.66210) (4221.34242 8095.77681) (4219.45701 8093.89140)))
("SF_SOLAR" 1 ((4228.88382 8076.92308) (4230.76923 8078.80848) (4232.65464 8076.92308) (4230.76923 8075.03767)))
("SF_SOLAR" 1 ((4240.19604 8107.08903) (4242.08145 8108.97432) (4243.96686 8107.08903) (4242.08145 8105.20362)))
("SF_SOLAR" 1 ((4240.19604 8058.06934) (4242.08145 8059.95475) (4243.96686 8058.06934) (4242.08145 8056.18405)))
("SF_SOLAR" 1 ((4247.73756 8176.84762) (4249.62296 8178.73303) (4251.50826 8176.84762) (4249.62296 8174.96233)))
("SF_SOLAR" 1 ((4247.73756 8110.85973) (4249.62296 8112.74514) (4251.50826 8110.85973) (4249.62296 8108.97432)))
("SF_SOLAR" 1 ((4247.73756 8092.00600) (4249.62296 8093.89140) (4251.50826 8092.00600) (4249.62296 8090.12070)))
("SF_SOLAR" 1 ((4249.62296 8041.10102) (4251.50826 8042.98643) (4253.39367 8041.10102) (4251.50826 8039.21572)))
("SF_SOLAR" 1 ((4259.04977 8095.77681) (4260.93518 8097.66210) (4262.82048 8095.77681) (4260.93518 8093.89140)))
("SF_SOLAR" 1 ((4262.82048 8076.92308) (4264.70588 8078.80848) (4266.59129 8076.92308) (4264.70588 8075.03767)))
("SF_SOLAR" 1 ((4262.82048 8024.13269) (4264.70588 8026.01810) (4266.59129 8024.13269) (4264.70588 8022.24740)))
("SF_SOLAR" 1 ((4270.36199 8076.92308) (4272.24740 8078.80848) (4274.13269 8076.92308) (4272.24740 8075.03767)))
("SF_SOLAR" 1 ((4274.13269 8061.84016) (4276.01810 8063.72545) (4277.90351 8061.84016) (4276.01810 8059.95475)))
("SF_SOLAR" 1 ((4274.13269 8009.04977) (4276.01810 8010.93518) (4277.90351 8009.04977) (4276.01810 8007.16437)))
("SF_PLANTING" 1 ((4277.90351 4223.22771) (4279.78880 4225.11312) (4281.67421 4223.22771) (4279.78880 4221.34242)))
("SF_SOLAR" 1 ((4281.67421 7992.08145) (4283.55962 7993.96686) (4285.44491 7992.08145) (4283.55962 7990.19604)))
("SF_SOLAR" 1 ((4285.44491 8042.98643) (4287.33032 8044.87183) (4289.21572 8042.98643) (4287.33032 8041.10102)))
("SF_SOLAR" 1 ((4292.98643 8042.98643) (4294.87183 8044.87183) (4296.75713 8042.98643) (4294.87183 8041.10102)))
("SF_SOLAR" 1 ((4294.87183 8026.01810) (4296.75713 8027.90351) (4298.64253 8026.01810) (4296.75713 8024.13269)))
("SF_SOLAR" 1 ((4296.75713 7975.11312) (4298.64253 7976.99853) (4300.52794 7975.11312) (4298.64253 7973.22771)))
("SF_SOLAR" 1 ((4304.29864 8027.90351) (4306.18405 8029.78880) (4308.06934 8027.90351) (4306.18405 8026.01810)))
("SF_SOLAR" 1 ((4308.06934 8005.27907) (4309.95475 8007.16437) (4311.84016 8005.27907) (4309.95475 8003.39367)))
("SF_SOLAR" 1 ((4308.06934 7960.03020) (4309.95475 7961.91550) (4311.84016 7960.03020) (4309.95475 7958.14480)))
("SF_SOLAR" 1 ((4317.49627 8009.04977) (4319.38156 8010.93518) (4321.26697 8009.04977) (4319.38156 8007.16437)))
("SF_SOLAR" 1 ((4317.49627 7990.19604) (4319.38156 7992.08145) (4321.26697 7990.19604) (4319.38156 7988.31075)))
("SF_SOLAR" 1 ((4319.38156 7941.17647) (4321.26697 7943.06188) (4323.15238 7941.17647) (4321.26697 7939.29106)))
("SF_SOLAR" 1 ((4328.80848 7993.96686) (4330.69378 7995.85215) (4332.57919 7993.96686) (4330.69378 7992.08145)))
("SF_SOLAR" 1 ((4330.69378 7971.34242) (4332.57919 7973.22771) (4334.46459 7971.34242) (4332.57919 7969.45701)))
("SF_SOLAR" 1 ((4330.69378 7926.09355) (4332.57919 7927.97885) (4334.46459 7926.09355) (4332.57919 7924.20814)))
("SF_SOLAR" 1 ((4330.69378 7846.90803) (4332.57919 7848.79333) (4334.46459 7846.90803) (4332.57919 7845.02262)))
("SF_SOLAR" 1 ((4334.46459 8124.05735) (4336.34989 8125.94265) (4338.23529 8124.05735) (4336.34989 8122.17195)))
("SF_SOLAR" 1 ((4342.00600 7960.03020) (4343.89140 7961.91550) (4345.77681 7960.03020) (4343.89140 7958.14480)))
("SF_SOLAR" 1 ((4342.00600 7907.23982) (4343.89140 7909.12523) (4345.77681 7907.23982) (4343.89140 7905.35441)))
("SF_SOLAR" 1 ((4351.43292 7941.17647) (4353.31821 7943.06188) (4355.20362 7941.17647) (4353.31821 7939.29106)))
("SF_SOLAR" 1 ((4360.85973 7944.94717) (4362.74514 7946.83258) (4364.63043 7944.94717) (4362.74514 7943.06188)))
("SF_SOLAR" 1 ((4362.74514 7924.20814) (4364.63043 7926.09355) (4366.51584 7924.20814) (4364.63043 7922.32274)))
("SF_SOLAR" 1 ((4366.51584 8078.80848) (4368.40124 8080.69378) (4370.28654 8078.80848) (4368.40124 8076.92308)))
("SF_SOLAR" 1 ((4368.40124 7846.90803) (4370.28654 7848.79333) (4372.17195 7846.90803) (4370.28654 7845.02262)))
("SF_SOLAR" 1 ((4372.17195 7929.86425) (4374.05735 7931.74966) (4375.94265 7929.86425) (4374.05735 7927.97885)))
("SF_PLANTING" 1 ((4375.26165 3474.05486) (4375.26165 3484.16290) (4389.14027 3495.31357) (4399.09989 3491.55000)
(4389.13405 3474.05486)))
("SF_SOLAR" 1 ((4398.56708 8195.70136) (4400.45249 8197.58676) (4402.33790 8195.70136) (4400.45249 8193.81595)))
("SF_SOLAR" 1 ((4402.33790 8152.33790) (4404.22319 8154.22319) (4406.10860 8152.33790) (4404.22319 8150.45249)))
("SF_SOLAR" 1 ((4402.33790 7958.14480) (4404.22319 7960.03020) (4406.10860 7958.14480) (4404.22319 7956.25939)))
("SF_SOLAR" 1 ((4406.10860 7877.07387) (4407.99400 7878.95928) (4409.87930 7877.07387) (4407.99400 7875.18857)))
("SF_SOLAR" 1 ((4406.10860 7861.99095) (4407.99400 7863.87636) (4409.87930 7861.99095) (4407.99400 7860.10554)))
("SF_SOLAR" 1 ((4409.87930 8176.84762) (4411.76471 8178.73303) (4413.65011 8176.84762) (4411.76471 8174.96233)))
("SF_SOLAR" 1 ((4424.96233 8152.33790) (4426.84762 8154.22319) (4428.73303 8152.33790) (4426.84762 8150.45249)))
("SF_SOLAR" 1 ((4424.96233 7886.50079) (4426.84762 7888.38609) (4428.73303 7886.50079) (4426.84762 7884.61538)))
("SF_SOLAR" 1 ((4443.81595 8122.17195) (4445.70136 8124.05735) (4447.58676 8122.17195) (4445.70136 8120.28654)))
("SF_SOLAR" 1 ((4447.58676 7920.43744) (4449.47206 7922.32274) (4451.35747 7920.43744) (4449.47206 7918.55204)))
("SF_SOLAR" 1 ((4451.35747 7856.33484) (4453.24287 7858.22025) (4455.12817 7856.33484) (4453.24287 7854.44943)))
("SF_SOLAR" 1 ((4470.21120 7922.32274) (4472.09649 7924.20814) (4473.98190 7922.32274) (4472.09649 7920.43744)))
("SF_SOLAR" 1 ((4473.98190 8193.81595) (4475.86731 8195.70136) (4477.75260 8193.81595) (4475.86731 8191.93066)))
("SF_SOLAR" 1 ((4473.98190 8180.61844) (4475.86731 8182.50373) (4477.75260 8180.61844) (4475.86731 8178.73303)))
("SF_SOLAR" 1 ((4475.86731 8146.68179) (4477.75260 8148.56708) (4479.63801 8146.68179) (4477.75260 8144.79638)))
("SF_PLANTING" 1 ((4506.03314 3354.07240) (4507.91855 3355.95781) (4509.80396 3354.07240) (4507.91855 3352.18699)))
("SF_SOLAR" 1 ((4507.91855 8054.29864) (4509.80396 8056.18405) (4511.68925 8054.29864) (4509.80396 8052.41324)))
("SF_SOLAR" 1 ((4511.68925 8176.84762) (4513.57466 8178.73303) (4515.46007 8176.84762) (4513.57466 8174.96233)))
("SF_SOLAR" 1 ((4515.46007 7918.55204) (4517.34536 7920.43744) (4519.23077 7918.55204) (4517.34536 7916.66663)))
("SF_SOLAR" 1 ((4534.31369 7984.53993) (4536.19910 7986.42534) (4538.08450 7984.53993) (4536.19910 7982.65464)))
("SF_SOLAR" 1 ((4538.08450 8131.59876) (4539.96980 8133.48416) (4541.85520 8131.59876) (4539.96980 8129.71346)))
("SF_SOLAR" 1 ((4556.93812 8037.33032) (4558.82353 8039.21572) (4560.70894 8037.33032) (4558.82353 8035.44491)))
("SF_SOLAR" 1 ((4579.56256 7993.96686) (4581.44796 7995.85215) (4583.33337 7993.96686) (4581.44796 7992.08145)))
("SF_SOLAR" 1 ((4581.44796 8042.98643) (4583.33337 8044.87183) (4585.21867 8042.98643) (4583.33337 8041.10102)))
("SF_SOLAR" 1 ((4588.98948 7990.19604) (4590.87477 7992.08145) (4592.76018 7990.19604) (4590.87477 7988.31075)))
("SF_SOLAR" 1 ((4605.95781 7867.64706) (4607.84310 7869.53247) (4609.72851 7867.64706) (4607.84310 7865.76165)))
("SF_SOLAR" 1 ((4630.46753 7843.13722) (4632.35294 7845.02262) (4634.23835 7843.13722) (4632.35294 7841.25192)))
("SF_PLANTING" 1 ((4651.20667 3840.49774) (4653.09197 3842.38314) (4654.97738 3840.49774) (4653.09197 3838.61233)))
("SF_SOLAR" 1 ((4662.51889 7958.14480) (4664.40419 7960.03020) (4666.28959 7958.14480) (4664.40419 7956.25939)))
("SF_SOLAR" 1 ((4670.06029 8195.70136) (4671.94570 8197.58676) (4673.83111 8195.70136) (4671.94570 8193.81595)))
("SF_SOLAR" 1 ((4673.83111 7886.50079) (4675.71640 7888.38609) (4677.60181 7886.50079) (4675.71640 7884.61538)))
("SF_MASONRY_AND_ARCH" 1 ((4677.60181 2379.33631) (4679.48722 2381.22172) (4681.37251 2379.33631) (4679.48722
2377.45102)))
("SF_PLANTING" 1 ((4681.37251 3842.38314) (4683.25792 3844.26844) (4685.14333 3842.38314) (4683.25792 3840.49774)))
("SF_SOLAR" 1 ((4719.07998 7956.25939) (4720.96527 7958.14480) (4722.85068 7956.25939) (4720.96527 7954.37410)))
("SF_SOLAR" 1 ((4719.07998 7914.78133) (4720.96527 7916.66663) (4722.85068 7914.78133) (4720.96527 7912.89593)))
("SF_SOLAR" 1 ((4722.85068 8182.50373) (4724.73609 8184.38914) (4726.62138 8182.50373) (4724.73609 8180.61844)))
("SF_MASONRY_AND_ARCH" 1 ((4739.81900 2281.29717) (4741.70441 2283.18247) (4743.58971 2281.29717) (4741.70441
2279.41176)))
("SF_SOLAR" 1 ((4741.70441 8050.52794) (4743.58971 8052.41324) (4745.47511 8050.52794) (4743.58971 8048.64253)))
("SF_SOLAR" 1 ((4741.70441 7926.09355) (4743.58971 7927.97885) (4745.47511 7926.09355) (4743.58971 7924.20814)))
("SF_SOLAR" 1 ((4745.47511 7950.60328) (4747.36052 7952.48869) (4749.24581 7950.60328) (4747.36052 7948.71799)))
("SF_SOLAR" 1 ((4760.55803 8110.85973) (4762.44344 8112.74514) (4764.32885 8110.85973) (4762.44344 8108.97432)))
("SF_SOLAR" 1 ((4771.87025 8005.27907) (4773.75566 8007.16437) (4775.64106 8005.27907) (4773.75566 8003.39367)))
("SF_SOLAR" 1 ((4781.29717 8084.46459) (4783.18247 8086.34989) (4785.06787 8084.46459) (4783.18247 8082.57919)))
("SF_SOLAR" 1 ((4786.95328 8152.33790) (4788.83857 8154.22319) (4790.72398 8152.33790) (4788.83857 8150.45249)))
("SF_SOLAR" 1 ((4792.60939 8063.72545) (4794.49468 8065.61086) (4796.38009 8063.72545) (4794.49468 8061.84016)))
("SF_SOLAR" 1 ((4802.03620 8054.29864) (4803.92161 8056.18405) (4805.80690 8054.29864) (4803.92161 8052.41324)))
("SF_SOLAR" 1 ((4809.57771 7950.60328) (4811.46301 7952.48869) (4813.34842 7950.60328) (4811.46301 7948.71799)))
("SF_SOLAR" 1 ((4826.54604 7999.62296) (4828.43133 8001.50826) (4830.31674 7999.62296) (4828.43133 7997.73756)))
("SF_SOLAR" 1 ((4839.74355 8046.75713) (4841.62896 8048.64253) (4843.51437 8046.75713) (4841.62896 8044.87183)))
("SF_SOLAR" 1 ((4839.74355 7995.85215) (4841.62896 7997.73756) (4843.51437 7995.85215) (4841.62896 7993.96686)))
("SF_SOLAR" 1 ((4854.82658 7865.76165) (4856.71188 7867.64706) (4858.59729 7865.76165) (4856.71188 7863.87636)))
("SF_SOLAR" 1 ((4866.13880 7941.17647) (4868.02410 7943.06188) (4869.90950 7941.17647) (4868.02410 7939.29106)))
("SF_SOLAR" 1 ((4873.68020 7950.60328) (4875.56561 7952.48869) (4877.45102 7950.60328) (4875.56561 7948.71799)))
("SF_SOLAR" 1 ((4884.99242 7882.72998) (4886.87783 7884.61538) (4888.76324 7882.72998) (4886.87783 7880.84468)))
("SF_SOLAR" 1 ((4884.99242 7867.64706) (4886.87783 7869.53247) (4888.76324 7867.64706) (4886.87783 7865.76165)))
("SF_SOLAR" 1 ((4900.07545 8120.28654) (4901.96075 8122.17195) (4903.84615 8120.28654) (4901.96075 8118.40124)))
("SF_PLANTING" 1 ((4913.27296 3995.09808) (4915.15837 3996.98337) (4917.04378 3995.09808) (4915.15837 3993.21267)))
("SF_SOLAR" 1 ((4922.69989 8031.67421) (4924.58518 8033.55962) (4926.47059 8031.67421) (4924.58518 8029.78880)))
("SF_PLANTING" 1 ((4935.89740 1093.51437) (4937.78281 1095.39966) (4939.66821 1093.51437) (4937.78281 1091.62896)))
("SF_SOLAR" 1 ((4945.32432 8050.52794) (4947.20962 8052.41324) (4949.09502 8050.52794) (4947.20962 8048.64253)))
("SF_PLANTING" 1 ((4950.83213 3588.53925) (4932.27477 3589.58869) (4927.46097 3585.81821) (4917.34672 3548.27195)
(4920.96912 3541.93507) (4947.20939 3545.69864) (4957.45871 3555.80667) (4958.38043 3574.66063)))
("SF_SOLAR" 1 ((4952.86572 8176.84762) (4954.75113 8178.73303) (4956.63654 8176.84762) (4954.75113 8174.96233)))
("SF_SOLAR" 1 ((4960.40724 7978.88382) (4962.29265 7980.76923) (4964.17794 7978.88382) (4962.29265 7976.99853)))
("SF_SOLAR" 1 ((4960.40724 7867.64706) (4962.29265 7869.53247) (4964.17794 7867.64706) (4962.29265 7865.76165)))
("SF_SOLAR" 1 ((4967.94876 7990.19604) (4969.83405 7992.08145) (4971.71946 7990.19604) (4969.83405 7988.31075)))
("SF_SOLAR" 1 ((4983.03167 8029.78880) (4984.91708 8031.67421) (4986.80238 8029.78880) (4984.91708 8027.90351)))
("SF_SOLAR" 1 ((5001.88541 7924.20814) (5003.77070 7926.09355) (5005.65611 7924.20814) (5003.77070 7922.32274)))
("SF_SOLAR" 1 ((5020.73903 8227.75260) (5022.62443 8229.63801) (5024.50984 8227.75260) (5022.62443 8225.86731)))
("SF_SOLAR" 1 ((5024.50984 7927.97885) (5026.39514 7929.86425) (5028.28054 7927.97885) (5026.39514 7926.09355)))
("SF_SOLAR" 1 ((5033.93665 8152.33790) (5035.82206 8154.22319) (5037.70735 8152.33790) (5035.82206 8150.45249)))
("SF_SOLAR" 1 ((5039.59276 8122.17195) (5041.47817 8124.05735) (5043.36346 8122.17195) (5041.47817 8120.28654)))
("SF_SOLAR" 1 ((5047.13428 8127.82805) (5049.01957 8129.71346) (5050.90498 8127.82805) (5049.01957 8125.94265)))
("SF_SOLAR" 1 ((5049.01957 8107.08903) (5050.90498 8108.97432) (5052.79038 8107.08903) (5050.90498 8105.20362)))
("SF_SOLAR" 1 ((5058.44649 8195.70136) (5060.33179 8197.58676) (5062.21719 8195.70136) (5060.33179 8193.81595)))
("SF_SOLAR" 1 ((5069.75871 8095.77681) (5071.64400 8097.66210) (5073.52941 8095.77681) (5071.64400 8093.89140)))
("SF_SOLAR" 1 ((5073.52941 8073.15238) (5075.41482 8075.03767) (5077.30011 8073.15238) (5075.41482 8071.26697)))
("SF_SOLAR" 1 ((5077.30011 8084.46459) (5079.18552 8086.34989) (5081.07093 8084.46459) (5079.18552 8082.57919)))
("SF_SOLAR" 1 ((5084.84163 8050.52794) (5086.72704 8052.41324) (5088.61233 8050.52794) (5086.72704 8048.64253)))
("SF_SOLAR" 1 ((5092.38314 8059.95475) (5094.26844 8061.84016) (5096.15385 8059.95475) (5094.26844 8058.06934)))
("SF_SOLAR" 1 ((5092.38314 7926.09355) (5094.26844 7927.97885) (5096.15385 7926.09355) (5094.26844 7924.20814)))
("SF_SOLAR" 1 ((5096.15385 8031.67421) (5098.03925 8033.55962) (5099.92455 8031.67421) (5098.03925 8029.78880)))
("SF_SOLAR" 1 ((5103.69536 8039.21572) (5105.58066 8041.10102) (5107.46606 8039.21572) (5105.58066 8037.33032)))
("SF_SOLAR" 1 ((5107.46606 8014.70588) (5109.35147 8016.59129) (5111.23676 8014.70588) (5109.35147 8012.82048)))
("SF_SOLAR" 1 ((5113.12217 8026.01810) (5115.00758 8027.90351) (5116.89287 8026.01810) (5115.00758 8024.13269)))
("SF_SOLAR" 1 ((5118.77828 7952.48869) (5120.66369 7954.37410) (5122.54898 7952.48869) (5120.66369 7950.60328)))
("SF_SOLAR" 1 ((5128.20509 7982.65464) (5130.09050 7984.53993) (5131.97590 7982.65464) (5130.09050 7980.76923)))
("SF_SOLAR" 1 ((5133.86120 7992.08145) (5135.74661 7993.96686) (5137.63201 7992.08145) (5135.74661 7990.19604)))
("SF_SOLAR" 1 ((5141.40271 7961.91550) (5143.28812 7963.80090) (5145.17342 7961.91550) (5143.28812 7960.03020)))
("SF_SOLAR" 1 ((5145.17342 7971.34242) (5147.05882 7973.22771) (5148.94423 7971.34242) (5147.05882 7969.45701)))
("SF_SOLAR" 1 ((5145.17342 7886.50079) (5147.05882 7888.38609) (5148.94423 7886.50079) (5147.05882 7884.61538)))
("SF_SOLAR" 1 ((5152.71493 7946.83258) (5154.60034 7948.71799) (5156.48563 7946.83258) (5154.60034 7944.94717)))
("SF_SOLAR" 1 ((5160.25645 8120.28654) (5162.14174 8122.17195) (5164.02715 8120.28654) (5162.14174 8118.40124)))
("SF_SOLAR" 1 ((5164.02715 7990.19604) (5165.91256 7992.08145) (5167.79785 7990.19604) (5165.91256 7988.31075)))
("SF_SOLAR" 1 ((5164.02715 7927.97885) (5165.91256 7929.86425) (5167.79785 7927.97885) (5165.91256 7926.09355)))
("SF_PLANTING" 1 ((5166.28767 378.28541) (5170.73993 411.00962) (5177.37274 421.26618) (5188.53654 424.89581)
(5199.84876 421.12466) (5213.72760 407.23982) (5213.72760 395.92760) (5203.61991 385.67172)))
("SF_SOLAR" 1 ((5169.68326 7937.40577) (5171.56867 7939.29106) (5173.45396 7937.40577) (5171.56867 7935.52036)))
("SF_SOLAR" 1 ((5171.56867 8018.47658) (5173.45396 8020.36199) (5175.33937 8018.47658) (5173.45396 8016.59129)))
("SF_SOLAR" 1 ((5175.33937 7843.13722) (5177.22477 7845.02262) (5179.11007 7843.13722) (5177.22477 7841.25192)))
("SF_SOLAR" 1 ((5177.22477 7926.09355) (5179.11007 7927.97885) (5180.99548 7926.09355) (5179.11007 7924.20814)))
("SF_PLANTING" 1 ((5196.07839 3576.54604) (5197.96380 3578.43133) (5199.84921 3576.54604) (5197.96380 3574.66063)))
("SF_SOLAR" 1 ((5209.27602 8174.96233) (5211.16143 8176.84762) (5213.04672 8174.96233) (5211.16143 8173.07692)))
("SF_SOLAR" 1 ((5220.58824 7858.22025) (5222.47364 7860.10554) (5224.35894 7858.22025) (5222.47364 7856.33484)))
("SF_SOLAR" 1 ((5228.12975 7984.53993) (5230.01505 7986.42534) (5231.90045 7984.53993) (5230.01505 7982.65464)))
("SF_SOLAR" 1 ((5228.12975 7892.15690) (5230.01505 7894.04219) (5231.90045 7892.15690) (5230.01505 7890.27149)))
("SF_SOLAR" 1 ((5239.44197 7918.55204) (5241.32726 7920.43744) (5243.21267 7918.55204) (5241.32726 7916.66663)))
("SF_SOLAR" 1 ((5246.98337 8118.40124) (5248.86878 8120.28654) (5250.75419 8118.40124) (5248.86878 8116.51584)))
("SF_PLANTING" 1 ((5250.75419 3921.56867) (5252.63948 3923.45396) (5254.52489 3921.56867) (5252.63948 3919.68326)))
("SF_SOLAR" 1 ((5254.52489 7882.72998) (5256.41029 7884.61538) (5258.29559 7882.72998) (5256.41029 7880.84468)))
("SF_SOLAR" 1 ((5262.06640 7888.38609) (5263.95170 7890.27149) (5265.83710 7888.38609) (5263.95170 7886.50079)))
("SF_SOLAR" 1 ((5265.83710 7869.53247) (5267.72251 7871.41776) (5269.60781 7869.53247) (5267.72251 7867.64706)))
("SF_SOLAR" 1 ((5277.14932 8197.58676) (5279.03473 8199.47206) (5280.92002 8197.58676) (5279.03473 8195.70136)))
("SF_SOLAR" 1 ((5279.03473 8146.68179) (5280.92002 8148.56708) (5282.80543 8146.68179) (5280.92002 8144.79638)))
("SF_SOLAR" 1 ((5292.23224 8050.52794) (5294.11765 8052.41324) (5296.00305 8050.52794) (5294.11765 8048.64253)))
("SF_PLANTING" 1 ((5294.11765 267.72251) (5296.00305 269.60781) (5297.88835 267.72251) (5296.00305 265.83710)))
("SF_SOLAR" 1 ((5328.05430 8086.34989) (5329.93971 8088.23529) (5331.82500 8086.34989) (5329.93971 8084.46459)))
("SF_SOLAR" 1 ((5341.25192 7926.09355) (5343.13722 7927.97885) (5345.02262 7926.09355) (5343.13722 7924.20814)))
("SF_SOLAR" 1 ((5345.02262 8131.59876) (5346.90803 8133.48416) (5348.79333 8131.59876) (5346.90803 8129.71346)))
("SF_PLANTING" 1 ((5346.90803 516.59129) (5348.79333 518.47658) (5350.67873 516.59129) (5348.79333 514.70588)))
("SF_SOLAR" 1 ((5363.87636 8152.33790) (5365.76165 8154.22319) (5367.64706 8152.33790) (5365.76165 8150.45249)))
("SF_SOLAR" 1 ((5380.84468 8009.04977) (5382.72998 8010.93518) (5384.61538 8009.04977) (5382.72998 8007.16437)))
("SF_SOLAR" 1 ((5392.15690 7992.08145) (5394.04219 7993.96686) (5395.92760 7992.08145) (5394.04219 7990.19604)))
("SF_SOLAR" 1 ((5403.46912 7973.22771) (5405.35441 7975.11312) (5407.23982 7973.22771) (5405.35441 7971.34242)))
("SF_SOLAR" 1 ((5412.89593 8031.67421) (5414.78133 8033.55962) (5416.66663 8031.67421) (5414.78133 8029.78880)))
("SF_SOLAR" 1 ((5416.66663 7963.80090) (5418.55204 7965.68631) (5420.43744 7963.80090) (5418.55204 7961.91550)))
("SF_SOLAR" 1 ((5431.74966 8050.52794) (5433.63495 8052.41324) (5435.52036 8050.52794) (5433.63495 8048.64253)))
("SF_SOLAR" 1 ((5431.74966 7858.22025) (5433.63495 7860.10554) (5435.52036 7858.22025) (5433.63495 7856.33484)))
("SF_SOLAR" 1 ((5450.60328 7984.53993) (5452.48869 7986.42534) (5454.37410 7984.53993) (5452.48869 7982.65464)))
("SF_SOLAR" 1 ((5454.37410 8050.52794) (5456.25939 8052.41324) (5458.14480 8050.52794) (5456.25939 8048.64253)))
("SF_SOLAR" 1 ((5469.45701 7850.67873) (5471.34242 7852.56414) (5473.22771 7850.67873) (5471.34242 7848.79333)))
("SF_SOLAR" 1 ((5476.99853 8174.96233) (5478.88382 8176.84762) (5480.76923 8174.96233) (5478.88382 8173.07692)))
("SF_SOLAR" 1 ((5476.99853 8071.26697) (5478.88382 8073.15238) (5480.76923 8071.26697) (5478.88382 8069.38156)))
("SF_SOLAR" 1 ((5476.99853 8022.24740) (5478.88382 8024.13269) (5480.76923 8022.24740) (5478.88382 8020.36199)))
("SF_SOLAR" 1 ((5499.62296 8050.52794) (5501.50826 8052.41324) (5503.39367 8050.52794) (5501.50826 8048.64253)))
("SF_SOLAR" 1 ((5503.39367 7865.76165) (5505.27907 7867.64706) (5507.16437 7865.76165) (5505.27907 7863.87636)))
("SF_SOLAR" 1 ((5518.47658 7865.76165) (5520.36199 7867.64706) (5522.24740 7865.76165) (5520.36199 7863.87636)))
("SF_SOLAR" 1 ((5522.24740 8050.52794) (5524.13269 8052.41324) (5526.01810 8050.52794) (5524.13269 8048.64253)))
("SF_SOLAR" 1 ((5529.78880 8180.61844) (5531.67421 8182.50373) (5533.55962 8180.61844) (5531.67421 8178.73303)))
("SF_SOLAR" 1 ((5539.21572 8146.68179) (5541.10102 8148.56708) (5542.98643 8146.68179) (5541.10102 8144.79638)))
("SF_SOLAR" 1 ((5544.87183 8050.52794) (5546.75713 8052.41324) (5548.64253 8050.52794) (5546.75713 8048.64253)))
("SF_SOLAR" 1 ((5567.49627 8176.84762) (5569.38156 8178.73303) (5571.26697 8176.84762) (5569.38156 8174.96233)))
("SF_SOLAR" 1 ((5573.15238 8101.43292) (5575.03767 8103.31821) (5576.92308 8101.43292) (5575.03767 8099.54751)))
("SF_SOLAR" 1 ((5593.89140 8061.84016) (5595.77681 8063.72545) (5597.66210 8061.84016) (5595.77681 8059.95475)))
("SF_SOLAR" 1 ((5605.20362 8092.00600) (5607.08903 8093.89140) (5608.97432 8092.00600) (5607.08903 8090.12070)))
("SF_SOLAR" 1 ((5620.28654 8039.21572) (5622.17195 8041.10102) (5624.05735 8039.21572) (5622.17195 8037.33032)))
("SF_SOLAR" 1 ((5631.59876 8020.36199) (5633.48416 8022.24740) (5635.36957 8020.36199) (5633.48416 8018.47658)))
("SF_SOLAR" 1 ((5635.36957 7948.71799) (5637.25486 7950.60328) (5639.14027 7948.71799) (5637.25486 7946.83258)))
("SF_SOLAR" 1 ((5639.14027 8009.04977) (5641.02568 8010.93518) (5642.91097 8009.04977) (5641.02568 8007.16437)))
("SF_PLANTING" 1 ((5648.72149 4048.56923) (5646.00090 4034.69729) (5663.49570 4024.73133) (5667.26618 4030.92670)
(5666.21629 4042.22579) (5659.87285 4048.56923)))
("SF_SOLAR" 1 ((5654.22319 7916.66663) (5656.10860 7918.55204) (5657.99400 7916.66663) (5656.10860 7914.78133)))
("SF_SOLAR" 1 ((5657.99400 8118.40124) (5659.87930 8120.28654) (5661.76471 8118.40124) (5659.87930 8116.51584)))
("SF_SOLAR" 1 ((5676.84762 7960.03020) (5678.73303 7961.91550) (5680.61844 7960.03020) (5678.73303 7958.14480)))
("SF_SOLAR" 1 ((5680.61844 8118.40124) (5682.50373 8120.28654) (5684.38914 8118.40124) (5682.50373 8116.51584)))
("SF_SOLAR" 1 ((5680.61844 7888.38609) (5682.50373 7890.27149) (5684.38914 7888.38609) (5682.50373 7886.50079)))
("SF_SOLAR" 1 ((5701.35747 7843.13722) (5703.24287 7845.02262) (5705.12817 7843.13722) (5703.24287 7841.25192)))
("SF_SOLAR" 1 ((5703.24287 8152.33790) (5705.12817 8154.22319) (5707.01357 8152.33790) (5705.12817 8150.45249)))
("SF_SOLAR" 1 ((5703.24287 7865.76165) (5705.12817 7867.64706) (5707.01357 7865.76165) (5705.12817 7863.87636)))
("SF_SOLAR" 1 ((5710.78428 7884.61538) (5712.66968 7886.50079) (5714.55509 7884.61538) (5712.66968 7882.72998)))
("SF_SOLAR" 1 ((5725.86731 8152.33790) (5727.75260 8154.22319) (5729.63801 8152.33790) (5727.75260 8150.45249)))
("SF_SOLAR" 1 ((5725.86731 7984.53993) (5727.75260 7986.42534) (5729.63801 7984.53993) (5727.75260 7982.65464)))
("SF_SOLAR" 1 ((5744.72093 8176.84762) (5746.60633 8178.73303) (5748.49174 8176.84762) (5746.60633 8174.96233)))
("SF_SOLAR" 1 ((5748.49174 8152.33790) (5750.37704 8154.22319) (5752.26244 8152.33790) (5750.37704 8150.45249)))
("SF_SOLAR" 1 ((5754.14785 7843.13722) (5756.03314 7845.02262) (5757.91855 7843.13722) (5756.03314 7841.25192)))
("SF_SOLAR" 1 ((5765.46007 8216.44038) (5767.34536 8218.32579) (5769.23077 8216.44038) (5767.34536 8214.55509)))
("SF_SOLAR" 1 ((5771.11618 7958.14480) (5773.00147 7960.03020) (5774.88688 7958.14480) (5773.00147 7956.25939)))
("SF_SOLAR" 1 ((5774.88688 7978.88382) (5776.77229 7980.76923) (5778.65758 7978.88382) (5776.77229 7976.99853)))
("SF_SOLAR" 1 ((5774.88688 7886.50079) (5776.77229 7888.38609) (5778.65758 7886.50079) (5776.77229 7884.61538)))
("SF_SOLAR" 1 ((5778.65758 8203.24287) (5780.54299 8205.12817) (5782.42839 8203.24287) (5780.54299 8201.35747)))
("SF_PLANTING" 1 ((5782.42839 296.00305) (5784.31369 297.88835) (5786.19910 296.00305) (5784.31369 294.11765)))
("SF_SOLAR" 1 ((5793.74061 8199.47206) (5795.62590 8201.35747) (5797.51131 8199.47206) (5795.62590 8197.58676)))
("SF_SOLAR" 1 ((5793.74061 7888.38609) (5795.62590 7890.27149) (5797.51131 7888.38609) (5795.62590 7886.50079)))
("SF_SOLAR" 1 ((5793.74061 7865.76165) (5795.62590 7867.64706) (5797.51131 7865.76165) (5795.62590 7863.87636)))
("SF_SOLAR" 1 ((5797.51131 8214.55509) (5799.39672 8216.44038) (5801.28201 8214.55509) (5799.39672 8212.66968)))
("SF_SOLAR" 1 ((5812.59423 8227.75260) (5814.47964 8229.63801) (5816.36505 8227.75260) (5814.47964 8225.86731)))
("SF_SOLAR" 1 ((5812.59423 8148.56708) (5814.47964 8150.45249) (5816.36505 8148.56708) (5814.47964 8146.68179)))
("SF_SOLAR" 1 ((5816.36505 7958.14480) (5818.25034 7960.03020) (5820.13575 7958.14480) (5818.25034 7956.25939)))
("SF_ARCHITECTURE" 1 ((5816.36505 4470.21120) (5818.25034 4472.09649) (5820.13575 4470.21120) (5818.25034 4468.32579)))
("SF_SOLAR" 1 ((5823.90645 8131.59876) (5825.79186 8133.48416) (5827.67726 8131.59876) (5825.79186 8129.71346)))
("SF_SOLAR" 1 ((5831.44796 8144.79638) (5833.33337 8146.68179) (5835.21867 8144.79638) (5833.33337 8142.91097)))
("SF_SOLAR" 1 ((5835.21867 8116.51584) (5837.10407 8118.40124) (5838.98948 8116.51584) (5837.10407 8114.63043)))
("SF_SOLAR" 1 ((5842.76018 8061.84016) (5844.64559 8063.72545) (5846.53088 8061.84016) (5844.64559 8059.95475)))
("SF_SOLAR" 1 ((5846.53088 8133.48416) (5848.41629 8135.36957) (5850.30170 8133.48416) (5848.41629 8131.59876)))
("SF_SOLAR" 1 ((5846.53088 8103.31821) (5848.41629 8105.20362) (5850.30170 8103.31821) (5848.41629 8101.43292)))
("SF_SOLAR" 1 ((5854.07240 8116.51584) (5855.95781 8118.40124) (5857.84310 8116.51584) (5855.95781 8114.63043)))
("SF_SOLAR" 1 ((5854.07240 8046.75713) (5855.95781 8048.64253) (5857.84310 8046.75713) (5855.95781 8044.87183)))
("SF_ARCHITECTURE" 1 ((5855.95781 5188.53699) (5857.84310 5190.42229) (5859.72851 5188.53699) (5857.84310 5186.65158)))
("SF_SOLAR" 1 ((5857.84310 8086.34989) (5859.72851 8088.23529) (5861.61391 8086.34989) (5859.72851 8084.46459)))
("SF_SOLAR" 1 ((5869.15532 8099.54751) (5871.04072 8101.43292) (5872.92613 8099.54751) (5871.04072 8097.66210)))
("SF_SOLAR" 1 ((5869.15532 8069.38156) (5871.04072 8071.26697) (5872.92613 8069.38156) (5871.04072 8067.49627)))
("SF_SOLAR" 1 ((5869.15532 8020.36199) (5871.04072 8022.24740) (5872.92613 8020.36199) (5871.04072 8018.47658)))
("SF_SOLAR" 1 ((5878.58224 8084.46459) (5880.46753 8086.34989) (5882.35294 8084.46459) (5880.46753 8082.57919)))
("SF_SOLAR" 1 ((5880.46753 8056.18405) (5882.35294 8058.06934) (5884.23835 8056.18405) (5882.35294 8054.29864)))
("SF_SOLAR" 1 ((5889.89446 8067.49627) (5891.77975 8069.38156) (5893.66516 8067.49627) (5891.77975 8065.61086)))
("SF_SOLAR" 1 ((5893.66516 8039.21572) (5895.55057 8041.10102) (5897.43586 8039.21572) (5895.55057 8037.33032)))
("SF_SOLAR" 1 ((5899.32127 8092.00600) (5901.20667 8093.89140) (5903.09197 8092.00600) (5901.20667 8090.12070)))
("SF_SOLAR" 1 ((5901.20667 8052.41324) (5903.09197 8054.29864) (5904.97738 8052.41324) (5903.09197 8050.52794)))
("SF_PLANTING" 1 ((5901.20667 1057.69231) (5903.09197 1059.57771) (5904.97738 1057.69231) (5903.09197 1055.80690)))
("SF_SOLAR" 1 ((5904.97738 8026.01810) (5906.86278 8027.90351) (5908.74808 8026.01810) (5906.86278 8024.13269)))
("SF_SOLAR" 1 ((5906.86278 7888.38609) (5908.74808 7890.27149) (5910.63348 7888.38609) (5908.74808 7886.50079)))
("SF_SOLAR" 1 ((5912.51889 8035.44491) (5914.40419 8037.33032) (5916.28959 8035.44491) (5914.40419 8033.55962)))
("SF_SOLAR" 1 ((5914.40419 8007.16437) (5916.28959 8009.04977) (5918.17500 8007.16437) (5916.28959 8005.27907)))
("SF_SOLAR" 1 ((5925.71640 8020.36199) (5927.60181 8022.24740) (5929.48722 8020.36199) (5927.60181 8018.47658)))
("SF_SOLAR" 1 ((5929.48722 7993.96686) (5931.37251 7995.85215) (5933.25792 7993.96686) (5931.37251 7992.08145)))
("SF_SOLAR" 1 ((5935.14333 8003.39367) (5937.02862 8005.27907) (5938.91403 8003.39367) (5937.02862 8001.50826)))
("SF_SOLAR" 1 ((5937.02862 8046.75713) (5938.91403 8048.64253) (5940.79943 8046.75713) (5938.91403 8044.87183)))
("SF_SOLAR" 1 ((5937.02862 7976.99853) (5938.91403 7978.88382) (5940.79943 7976.99853) (5938.91403 7975.11312)))
("SF_SOLAR" 1 ((5940.79943 7886.50079) (5942.68473 7888.38609) (5944.57014 7886.50079) (5942.68473 7884.61538)))
("SF_SOLAR" 1 ((5944.57014 7988.31075) (5946.45554 7990.19604) (5948.34084 7988.31075) (5946.45554 7986.42534)))
("SF_SOLAR" 1 ((5948.34084 7867.64706) (5950.22624 7869.53247) (5952.11165 7867.64706) (5950.22624 7865.76165)))
("SF_SOLAR" 1 ((5952.11165 7960.03020) (5953.99695 7961.91550) (5955.88235 7960.03020) (5953.99695 7958.14480)))
("SF_SOLAR" 1 ((5959.65305 7975.11312) (5961.53846 7976.99853) (5963.42387 7975.11312) (5961.53846 7973.22771)))
("SF_SOLAR" 1 ((5959.65305 7943.06188) (5961.53846 7944.94717) (5963.42387 7943.06188) (5961.53846 7941.17647)))
("SF_SOLAR" 1 ((5967.19457 7956.25939) (5969.07998 7958.14480) (5970.96527 7956.25939) (5969.07998 7954.37410)))
("SF_SOLAR" 1 ((5970.96527 8031.67421) (5972.85068 8033.55962) (5974.73609 8031.67421) (5972.85068 8029.78880)))
("SF_SOLAR" 1 ((5970.96527 7927.97885) (5972.85068 7929.86425) (5974.73609 7927.97885) (5972.85068 7926.09355)))
("SF_SOLAR" 1 ((5978.50679 7941.17647) (5980.39219 7943.06188) (5982.27749 7941.17647) (5980.39219 7939.29106)))
("SF_SOLAR" 1 ((5991.70441 7929.86425) (5993.58971 7931.74966) (5995.47511 7929.86425) (5993.58971 7927.97885)))
("SF_PLANTING" 1 ((5997.36052 3944.19310) (5999.24581 3946.07839) (6001.13122 3944.19310) (5999.24581 3942.30769)))
("SF_SOLAR" 1 ((6019.98495 8050.52794) (6021.87025 8052.41324) (6023.75566 8050.52794) (6021.87025 8048.64253)))
("SF_SOLAR" 1 ((6019.98495 7990.19604) (6021.87025 7992.08145) (6023.75566 7990.19604) (6021.87025 7988.31075)))
("SF_SOLAR" 1 ((6021.87025 7869.53247) (6023.75566 7871.41776) (6025.64106 7869.53247) (6023.75566 7867.64706)))
("SF_SOLAR" 1 ((6029.41176 8195.70136) (6031.29717 8197.58676) (6033.18247 8195.70136) (6031.29717 8193.81595)))
("SF_SOLAR" 1 ((6031.29717 8176.84762) (6033.18247 8178.73303) (6035.06787 8176.84762) (6033.18247 8174.96233)))
("SF_SOLAR" 1 ((6042.60939 8227.75260) (6044.49468 8229.63801) (6046.38009 8227.75260) (6044.49468 8225.86731)))
("SF_SOLAR" 1 ((6046.38009 7880.84468) (6048.26550 7882.72998) (6050.15079 7880.84468) (6048.26550 7878.95928)))
("SF_SOLAR" 1 ((6046.38009 7871.41776) (6048.26550 7873.30317) (6050.15079 7871.41776) (6048.26550 7869.53247)))
("SF_SOLAR" 1 ((6061.46301 8195.70136) (6063.34842 8197.58676) (6065.23382 8195.70136) (6063.34842 8193.81595)))
("SF_SOLAR" 1 ((6061.46301 8050.52794) (6063.34842 8052.41324) (6065.23382 8050.52794) (6063.34842 8048.64253)))
("SF_SOLAR" 1 ((6084.08744 8182.50373) (6085.97285 8184.38914) (6087.85826 8182.50373) (6085.97285 8180.61844)))
("SF_SOLAR" 1 ((6084.08744 8069.38156) (6085.97285 8071.26697) (6087.85826 8069.38156) (6085.97285 8067.49627)))
("SF_PLANTING" 1 ((6085.81821 3577.07240) (6078.43111 3574.49910) (6060.78201 3555.80667) (6059.73258 3533.18914)
(6063.50305 3526.85226) (6082.05385 3530.60973) (6090.63812 3544.49446) (6089.58869 3570.88326)))
("SF_SOLAR" 1 ((6087.85826 7960.03020) (6089.74355 7961.91550) (6091.62896 7960.03020) (6089.74355 7958.14480)))
("SF_SOLAR" 1 ((6102.94118 8197.58676) (6104.82658 8199.47206) (6106.71188 8197.58676) (6104.82658 8195.70136)))
("SF_SOLAR" 1 ((6104.82658 8107.08903) (6106.71188 8108.97432) (6108.59729 8107.08903) (6106.71188 8105.20362)))
("SF_SOLAR" 1 ((6116.13880 8105.20362) (6118.02410 8107.08903) (6119.90950 8105.20362) (6118.02410 8103.31821)))
("SF_SOLAR" 1 ((6133.10713 8084.46459) (6134.99242 8086.34989) (6136.87783 8084.46459) (6134.99242 8082.57919)))
("SF_PLANTING" 1 ((6133.10713 3785.82206) (6134.99242 3787.70735) (6136.87783 3785.82206) (6134.99242 3783.93665)))
("SF_PLANTING" 1 ((6148.19005 3403.09197) (6150.07545 3404.97738) (6151.96075 3403.09197) (6150.07545 3401.20667)))
("SF_SOLAR" 1 ((6155.73156 7926.09355) (6157.61686 7927.97885) (6159.50226 7926.09355) (6157.61686 7924.20814)))
("SF_SOLAR" 1 ((6163.27296 8041.10102) (6165.15837 8042.98643) (6167.04378 8041.10102) (6165.15837 8039.21572)))
("SF_SOLAR" 1 ((6174.58518 8020.36199) (6176.47059 8022.24740) (6178.35600 8020.36199) (6176.47059 8018.47658)))
("SF_SOLAR" 1 ((6185.89740 7886.50079) (6187.78281 7888.38609) (6189.66821 7886.50079) (6187.78281 7884.61538)))
("SF_SOLAR" 1 ((6197.20962 7993.96686) (6199.09502 7995.85215) (6200.98043 7993.96686) (6199.09502 7992.08145)))
("SF_SOLAR" 1 ((6197.20962 7971.34242) (6199.09502 7973.22771) (6200.98043 7971.34242) (6199.09502 7969.45701)))
("SF_SOLAR" 1 ((6197.20962 7854.44943) (6199.09502 7856.33484) (6200.98043 7854.44943) (6199.09502 7852.56414)))
("SF_SOLAR" 1 ((6200.98043 8152.33790) (6202.86572 8154.22319) (6204.75113 8152.33790) (6202.86572 8150.45249)))
("SF_SOLAR" 1 ((6208.52183 7978.88382) (6210.40724 7980.76923) (6212.29265 7978.88382) (6210.40724 7976.99853)))
("SF_SOLAR" 1 ((6234.91708 8152.33790) (6236.80238 8154.22319) (6238.68778 8152.33790) (6236.80238 8150.45249)))
("SF_SOLAR" 1 ((6238.68778 7869.53247) (6240.57319 7871.41776) (6242.45848 7869.53247) (6240.57319 7867.64706)))
("SF_SOLAR" 1 ((6250.00000 7984.53993) (6251.88541 7986.42534) (6253.77070 7984.53993) (6251.88541 7982.65464)))
("SF_SOLAR" 1 ((6265.08292 8027.90351) (6266.96833 8029.78880) (6268.85373 8027.90351) (6266.96833 8026.01810)))
("SF_SOLAR" 1 ((6268.85373 8152.33790) (6270.73903 8154.22319) (6272.62443 8152.33790) (6270.73903 8150.45249)))
("SF_SOLAR" 1 ((6280.16595 7950.60328) (6282.05124 7952.48869) (6283.93665 7950.60328) (6282.05124 7948.71799)))
("SF_SOLAR" 1 ((6287.70735 7958.14480) (6289.59276 7960.03020) (6291.47817 7958.14480) (6289.59276 7956.25939)))
("SF_SOLAR" 1 ((6291.47817 8152.33790) (6293.36346 8154.22319) (6295.24887 8152.33790) (6293.36346 8150.45249)))
("SF_SOLAR" 1 ((6291.47817 8005.27907) (6293.36346 8007.16437) (6295.24887 8005.27907) (6293.36346 8003.39367)))
("SF_SOLAR" 1 ((6314.10260 8152.33790) (6315.98790 8154.22319) (6317.87330 8152.33790) (6315.98790 8150.45249)))
("SF_SOLAR" 1 ((6321.64400 8176.84762) (6323.52941 8178.73303) (6325.41482 8176.84762) (6323.52941 8174.96233)))
("SF_SOLAR" 1 ((6332.95622 8069.38156) (6334.84163 8071.26697) (6336.72704 8069.38156) (6334.84163 8067.49627)))
("SF_MASONRY_AND_ARCH" 1 ((6336.72704 2609.35147) (6338.61233 2611.23676) (6340.49774 2609.35147) (6338.61233
2607.46606)))
("SF_SOLAR" 1 ((6349.92455 8191.93066) (6351.80995 8193.81595) (6353.69536 8191.93066) (6351.80995 8190.04525)))
("SF_SOLAR" 1 ((6359.35147 8182.50373) (6361.23676 8184.38914) (6363.12217 8182.50373) (6361.23676 8180.61844)))
("SF_SOLAR" 1 ((6359.35147 8076.92308) (6361.23676 8078.80848) (6363.12217 8076.92308) (6361.23676 8075.03767)))
("SF_MASONRY_AND_ARCH" 1 ((6365.01403 1503.16267) (6353.69536 1512.06731) (6353.69536 1606.33484) (6353.69536
1625.18948) (6353.69536 1704.37500) (6353.69536 1723.22681) (6357.45984 2130.46731) (6353.70249 2153.09174) (6357.16991
2187.32466) (6360.94038 2191.09581) (6383.86120 2189.59548) (6383.86120 2179.48744) (6383.86120 1576.16799) (6383.86120
1519.60690)))
("SF_SOLAR" 1 ((6378.20509 8076.92308) (6380.09050 8078.80848) (6381.97590 8076.92308) (6380.09050 8075.03767)))
("SF_SOLAR" 1 ((6378.20509 7924.20814) (6380.09050 7926.09355) (6381.97590 7924.20814) (6380.09050 7922.32274)))
("SF_SOLAR" 1 ((6398.94423 8127.82805) (6400.82952 8129.71346) (6402.71493 8127.82805) (6400.82952 8125.94265)))
("SF_SOLAR" 1 ((6423.45396 8103.31821) (6425.33937 8105.20362) (6427.22477 8103.31821) (6425.33937 8101.43292)))
("SF_SOLAR" 1 ((6427.22477 8073.15238) (6429.11007 8075.03767) (6430.99548 8073.15238) (6429.11007 8071.26697)))
("SF_SOLAR" 1 ((6434.76618 8082.57919) (6436.65158 8084.46459) (6438.53699 8082.57919) (6436.65158 8080.69378)))
("SF_SOLAR" 1 ((6453.61991 8127.82805) (6455.50532 8129.71346) (6457.39061 8127.82805) (6455.50532 8125.94265)))
("SF_SOLAR" 1 ((6461.16143 7924.20814) (6463.04672 7926.09355) (6464.93213 7924.20814) (6463.04672 7922.32274)))
("SF_SOLAR" 1 ((6466.81753 8120.28654) (6468.70283 8122.17195) (6470.58824 8120.28654) (6468.70283 8118.40124)))
("SF_SOLAR" 1 ((6466.81753 8033.55962) (6468.70283 8035.44491) (6470.58824 8033.55962) (6468.70283 8031.67421)))
("SF_SOLAR" 1 ((6512.06640 7971.34242) (6513.95170 7973.22771) (6515.83710 7971.34242) (6513.95170 7969.45701)))
("SF_SOLAR" 1 ((6529.03473 8084.46459) (6530.92002 8086.34989) (6532.80543 8084.46459) (6530.92002 8082.57919)))
("SF_SOLAR" 1 ((6540.34695 7886.50079) (6542.23224 7888.38609) (6544.11765 7886.50079) (6542.23224 7884.61538)))
("SF_SOLAR" 1 ((6547.88835 7931.74966) (6549.77376 7933.63495) (6551.65916 7931.74966) (6549.77376 7929.86425)))
("SF_SOLAR" 1 ((6570.51278 7850.67873) (6572.39819 7852.56414) (6574.28360 7850.67873) (6572.39819 7848.79333)))
("SF_SOLAR" 1 ((6574.28360 8031.67421) (6576.16889 8033.55962) (6578.05430 8031.67421) (6576.16889 8029.78880)))
("SF_SOLAR" 1 ((6574.28360 7990.19604) (6576.16889 7992.08145) (6578.05430 7990.19604) (6576.16889 7988.31075)))
("SF_SOLAR" 1 ((6574.28360 7869.53247) (6576.16889 7871.41776) (6578.05430 7869.53247) (6576.16889 7867.64706)))
("SF_SOLAR" 1 ((6585.59581 8176.84762) (6587.48111 8178.73303) (6589.36652 8176.84762) (6587.48111 8174.96233)))
("SF_PLANTING" 1 ((6587.48111 1114.25339) (6589.36652 1116.13880) (6591.25192 1114.25339) (6589.36652 1112.36799)))
("SF_SOLAR" 1 ((6602.56414 8227.75260) (6604.44943 8229.63801) (6606.33484 8227.75260) (6604.44943 8225.86731)))
("SF_SOLAR" 1 ((6611.99095 7886.50079) (6613.87636 7888.38609) (6615.76165 7886.50079) (6613.87636 7884.61538)))
("SF_SOLAR" 1 ((6613.87636 7865.76165) (6615.76165 7867.64706) (6617.64706 7865.76165) (6615.76165 7863.87636)))
("SF_SOLAR" 1 ((6619.53247 8050.52794) (6621.41776 8052.41324) (6623.30317 8050.52794) (6621.41776 8048.64253)))
("SF_MASONRY_AND_ARCH" 1 ((6632.72998 1385.74661) (6634.61538 1387.63201) (6636.50079 1385.74661) (6634.61538
1383.86120)))
("SF_SOLAR" 1 ((6638.38609 8171.19152) (6640.27149 8173.07692) (6642.15690 8171.19152) (6640.27149 8169.30622)))
("SF_SOLAR" 1 ((6642.15690 8031.67421) (6644.04219 8033.55962) (6645.92760 8031.67421) (6644.04219 8029.78880)))
("SF_SOLAR" 1 ((6644.04219 8227.75260) (6645.92760 8229.63801) (6647.81301 8227.75260) (6645.92760 8225.86731)))
("SF_SOLAR" 1 ((6649.69830 8171.19152) (6651.58371 8173.07692) (6653.46912 8171.19152) (6651.58371 8169.30622)))
("SF_SOLAR" 1 ((6649.69830 8152.33790) (6651.58371 8154.22319) (6653.46912 8152.33790) (6651.58371 8150.45249)))
("SF_SOLAR" 1 ((6666.66663 8152.33790) (6668.55204 8154.22319) (6670.43744 8152.33790) (6668.55204 8150.45249)))
("SF_SOLAR" 1 ((6666.66663 8022.24740) (6668.55204 8024.13269) (6670.43744 8022.24740) (6668.55204 8020.36199)))
("SF_SOLAR" 1 ((6672.32274 8124.05735) (6674.20814 8125.94265) (6676.09355 8124.05735) (6674.20814 8122.17195)))
("SF_SOLAR" 1 ((6676.09355 8223.98190) (6677.97885 8225.86731) (6679.86425 8223.98190) (6677.97885 8222.09649)))
("SF_SOLAR" 1 ((6679.86425 8197.58676) (6681.74966 8199.47206) (6683.63495 8197.58676) (6681.74966 8195.70136)))
("SF_SOLAR" 1 ((6679.86425 8131.59876) (6681.74966 8133.48416) (6683.63495 8131.59876) (6681.74966 8129.71346)))
("SF_SOLAR" 1 ((6683.63495 8110.85973) (6685.52036 8112.74514) (6687.40577 8110.85973) (6685.52036 8108.97432)))
("SF_SOLAR" 1 ((6689.29106 8118.40124) (6691.17647 8120.28654) (6693.06188 8118.40124) (6691.17647 8116.51584)))
("SF_SOLAR" 1 ((6691.17647 8182.50373) (6693.06188 8184.38914) (6694.94717 8182.50373) (6693.06188 8180.61844)))
("SF_SOLAR" 1 ((6698.71799 8178.73303) (6700.60328 8180.61844) (6702.48869 8178.73303) (6700.60328 8176.84762)))
("SF_SOLAR" 1 ((6704.37410 8073.15238) (6706.25939 8075.03767) (6708.14480 8073.15238) (6706.25939 8071.26697)))
("SF_SOLAR" 1 ((6713.80090 8084.46459) (6715.68631 8086.34989) (6717.57161 8084.46459) (6715.68631 8082.57919)))
("SF_SOLAR" 1 ((6713.80090 8059.95475) (6715.68631 8061.84016) (6717.57161 8059.95475) (6715.68631 8058.06934)))
("SF_PLANTING" 1 ((6713.80090 1187.78281) (6715.68631 1189.66821) (6717.57161 1187.78281) (6715.68631 1185.89740)))
("SF_SOLAR" 1 ((6725.11312 8065.61086) (6726.99853 8067.49627) (6728.88382 8065.61086) (6726.99853 8063.72545)))
("SF_SOLAR" 1 ((6728.88382 8039.21572) (6730.76923 8041.10102) (6732.65464 8039.21572) (6730.76923 8037.33032)))
("SF_SOLAR" 1 ((6732.65464 7924.20814) (6734.53993 7926.09355) (6736.42534 7924.20814) (6734.53993 7922.32274)))
("SF_SOLAR" 1 ((6736.42534 8092.00600) (6738.31075 8093.89140) (6740.19604 8092.00600) (6738.31075 8090.12070)))
("SF_SOLAR" 1 ((6736.42534 8050.52794) (6738.31075 8052.41324) (6740.19604 8050.52794) (6738.31075 8048.64253)))
("SF_SOLAR" 1 ((6745.85215 8031.67421) (6747.73756 8033.55962) (6749.62296 8031.67421) (6747.73756 8029.78880)))
("SF_SOLAR" 1 ((6747.73756 8005.27907) (6749.62296 8007.16437) (6751.50826 8005.27907) (6749.62296 8003.39367)))
("SF_SOLAR" 1 ((6757.16437 8012.82048) (6759.04977 8014.70588) (6760.93518 8012.82048) (6759.04977 8010.93518)))
("SF_SOLAR" 1 ((6759.04977 7986.42534) (6760.93518 7988.31075) (6762.82048 7986.42534) (6760.93518 7984.53993)))
("SF_SOLAR" 1 ((6768.47658 7993.96686) (6770.36199 7995.85215) (6772.24740 7993.96686) (6770.36199 7992.08145)))
("SF_SOLAR" 1 ((6772.24740 8041.10102) (6774.13269 8042.98643) (6776.01810 8041.10102) (6774.13269 8039.21572)))
("SF_SOLAR" 1 ((6772.24740 7971.34242) (6774.13269 7973.22771) (6776.01810 7971.34242) (6774.13269 7969.45701)))
("SF_MASONRY_AND_ARCH" 1 ((6776.01810 2475.49016) (6777.90351 2477.37557) (6779.78880 2475.49016) (6777.90351
2473.60486)))
("SF_SOLAR" 1 ((6777.90351 8120.28654) (6779.78880 8122.17195) (6781.67421 8120.28654) (6779.78880 8118.40124)))
("SF_SOLAR" 1 ((6779.78880 7978.88382) (6781.67421 7980.76923) (6783.55962 7978.88382) (6781.67421 7976.99853)))
("SF_SOLAR" 1 ((6781.67421 7958.14480) (6783.55962 7960.03020) (6785.44491 7958.14480) (6783.55962 7956.25939)))
("SF_SOLAR" 1 ((6791.10102 7963.80090) (6792.98643 7965.68631) (6794.87183 7963.80090) (6792.98643 7961.91550)))
("SF_SOLAR" 1 ((6792.98643 7941.17647) (6794.87183 7943.06188) (6796.75713 7941.17647) (6794.87183 7939.29106)))
("SF_SOLAR" 1 ((6796.75713 7850.67873) (6798.64253 7852.56414) (6800.52794 7850.67873) (6798.64253 7848.79333)))
("SF_SOLAR" 1 ((6800.52794 8133.48416) (6802.41324 8135.36957) (6804.29864 8133.48416) (6802.41324 8131.59876)))
("SF_PLANTING" 1 ((6800.52794 460.03020) (6802.41324 461.91550) (6804.29864 460.03020) (6802.41324 458.14480)))
("SF_SOLAR" 1 ((6802.41324 7944.94717) (6804.29864 7946.83258) (6806.18405 7944.94717) (6804.29864 7943.06188)))
("SF_SOLAR" 1 ((6806.18405 7926.09355) (6808.06934 7927.97885) (6809.95475 7926.09355) (6808.06934 7924.20814)))
("SF_SOLAR" 1 ((6806.18405 7869.53247) (6808.06934 7871.41776) (6809.95475 7869.53247) (6808.06934 7867.64706)))
("SF_SOLAR" 1 ((6811.84016 7933.63495) (6813.72545 7935.52036) (6815.61086 7933.63495) (6813.72545 7931.74966)))
("SF_SOLAR" 1 ((6823.15238 8223.98190) (6825.03767 8225.86731) (6826.92308 8223.98190) (6825.03767 8222.09649)))
("SF_SOLAR" 1 ((6823.15238 8197.58676) (6825.03767 8199.47206) (6826.92308 8197.58676) (6825.03767 8195.70136)))
("SF_SOLAR" 1 ((6823.15238 8174.96233) (6825.03767 8176.84762) (6826.92308 8174.96233) (6825.03767 8173.07692)))
("SF_SOLAR" 1 ((6823.15238 8050.52794) (6825.03767 8052.41324) (6826.92308 8050.52794) (6825.03767 8048.64253)))
("SF_PLANTING" 1 ((6826.92308 641.02568) (6828.80848 642.91097) (6830.69378 641.02568) (6828.80848 639.14027)))
("SF_MASONRY_AND_ARCH" 1 ((6828.80848 921.94570) (6830.69378 923.83111) (6832.57919 921.94570) (6830.69378 920.06029)))
("SF_SOLAR" 1 ((6845.77681 8182.50373) (6847.66210 8184.38914) (6849.54751 8182.50373) (6847.66210 8180.61844)))
("SF_SOLAR" 1 ((6845.77681 8082.57919) (6847.66210 8084.46459) (6849.54751 8082.57919) (6847.66210 8080.69378)))
("SF_SOLAR" 1 ((6845.77681 8050.52794) (6847.66210 8052.41324) (6849.54751 8050.52794) (6847.66210 8048.64253)))
("SF_MASONRY_AND_ARCH" 1 ((6849.54751 1595.02262) (6851.43292 1596.90803) (6853.31821 1595.02262) (6851.43292
1593.13722)))
("SF_SOLAR" 1 ((6858.97432 8180.61844) (6860.85973 8182.50373) (6862.74514 8180.61844) (6860.85973 8178.73303)))
("SF_SOLAR" 1 ((6891.02568 8223.98190) (6892.91097 8225.86731) (6894.79638 8223.98190) (6892.91097 8222.09649)))
("SF_SOLAR" 1 ((6894.79638 8050.52794) (6896.68179 8052.41324) (6898.56708 8050.52794) (6896.68179 8048.64253)))
("SF_SOLAR" 1 ((6906.10860 8195.70136) (6907.99400 8197.58676) (6909.87930 8195.70136) (6907.99400 8193.81595)))
("SF_SOLAR" 1 ((6909.87930 8133.48416) (6911.76471 8135.36957) (6913.65011 8133.48416) (6911.76471 8131.59876)))
("SF_SOLAR" 1 ((6909.87930 8050.52794) (6911.76471 8052.41324) (6913.65011 8050.52794) (6911.76471 8048.64253)))
("SF_MASONRY_AND_ARCH" 1 ((6911.76471 1953.24287) (6913.65011 1955.12817) (6915.53541 1953.24287) (6913.65011
1951.35747)))
("SF_SOLAR" 1 ((6913.65011 8112.74514) (6915.53541 8114.63043) (6917.42081 8112.74514) (6915.53541 8110.85973)))
("SF_SOLAR" 1 ((6924.96233 8180.61844) (6926.84762 8182.50373) (6928.73303 8180.61844) (6926.84762 8178.73303)))
("SF_MASONRY_AND_ARCH" 1 ((6930.61844 2249.24581) (6932.50373 2251.13122) (6934.38914 2249.24581) (6932.50373
2247.36052)))
("SF_MASONRY_AND_ARCH" 1 ((6934.38914 1101.05577) (6936.27455 1102.94118) (6938.15984 1101.05577) (6936.27455
1099.17048)))
("SF_SOLAR" 1 ((6953.24287 8059.95475) (6955.12817 8061.84016) (6957.01357 8059.95475) (6955.12817 8058.06934)))
("SF_MASONRY_AND_ARCH" 1 ((6960.78428 1027.52636) (6962.66968 1029.41176) (6964.55509 1027.52636) (6962.66968
1025.64106)))
("SF_SOLAR" 1 ((6973.98190 8020.36199) (6975.86731 8022.24740) (6977.75260 8020.36199) (6975.86731 8018.47658)))
("SF_MASONRY_AND_ARCH" 1 ((6979.63801 3129.71346) (6981.52342 3131.59876) (6983.40871 3129.71346) (6981.52342
3127.82805)))
("SF_MASONRY_AND_ARCH" 1 ((6979.63801 3039.21572) (6981.52342 3041.10102) (6983.40871 3039.21572) (6981.52342
3037.33032)))
("SF_SOLAR" 1 ((6981.52342 8152.33790) (6983.40871 8154.22319) (6985.29412 8152.33790) (6983.40871 8150.45249)))
("SF_SOLAR" 1 ((7000.37704 7914.78133) (7002.26244 7916.66663) (7004.14785 7914.78133) (7002.26244 7912.89593)))
("SF_MASONRY_AND_ARCH" 1 ((7002.26244 2654.60034) (7004.14785 2656.48563) (7006.03314 2654.60034) (7004.14785
2652.71493)))
("SF_SOLAR" 1 ((7004.14785 8046.75713) (7006.03314 8048.64253) (7007.91855 8046.75713) (7006.03314 8044.87183)))
("SF_SOLAR" 1 ((7006.03314 7992.08145) (7007.91855 7993.96686) (7009.80396 7992.08145) (7007.91855 7990.19604)))
("SF_SOLAR" 1 ((7011.68925 7975.11312) (7013.57466 7976.99853) (7015.46007 7975.11312) (7013.57466 7973.22771)))
("SF_MASONRY_AND_ARCH" 1 ((7023.00147 2937.40577) (7024.88688 2939.29106) (7026.77229 2937.40577) (7024.88688
2935.52036)))
("SF_SOLAR" 1 ((7024.88688 7963.80090) (7026.77229 7965.68631) (7028.65758 7963.80090) (7026.77229 7961.91550)))
("SF_SOLAR" 1 ((7026.77229 8152.33790) (7028.65758 8154.22319) (7030.54299 8152.33790) (7028.65758 8150.45249)))
("SF_SOLAR" 1 ((7032.42839 7937.40577) (7034.31369 7939.29106) (7036.19910 7937.40577) (7034.31369 7935.52036)))
("SF_MASONRY_AND_ARCH" 1 ((7041.85520 3016.59129) (7043.74061 3018.47658) (7045.62590 3016.59129) (7043.74061
3014.70588)))
("SF_SOLAR" 1 ((7045.62590 7933.63495) (7047.51131 7935.52036) (7049.39672 7933.63495) (7047.51131 7931.74966)))
("SF_SOLAR" 1 ((7045.62590 7850.67873) (7047.51131 7852.56414) (7049.39672 7850.67873) (7047.51131 7848.79333)))
("SF_SOLAR" 1 ((7049.39672 8180.61844) (7051.28201 8182.50373) (7053.16742 8180.61844) (7051.28201 8178.73303)))
("SF_SOLAR" 1 ((7049.39672 8152.33790) (7051.28201 8154.22319) (7053.16742 8152.33790) (7051.28201 8150.45249)))
("SF_SOLAR" 1 ((7055.05283 7869.53247) (7056.93812 7871.41776) (7058.82353 7869.53247) (7056.93812 7867.64706)))
("SF_SOLAR" 1 ((7072.02115 7856.33484) (7073.90645 7858.22025) (7075.79186 7856.33484) (7073.90645 7854.44943)))
("SF_SOLAR" 1 ((7092.76018 8122.17195) (7094.64559 8124.05735) (7096.53088 8122.17195) (7094.64559 8120.28654)))
("SF_MASONRY_AND_ARCH" 1 ((7096.53088 3186.27455) (7098.41629 3188.15984) (7100.30170 3186.27455) (7098.41629
3184.38914)))
("SF_SOLAR" 1 ((7105.95781 7869.53247) (7107.84310 7871.41776) (7109.72851 7869.53247) (7107.84310 7867.64706)))
("SF_MASONRY_AND_ARCH" 1 ((7113.49921 1926.84762) (7115.38462 1928.73303) (7117.27002 1926.84762) (7115.38462
1924.96233)))
("SF_SOLAR" 1 ((7115.38462 8022.24740) (7117.27002 8024.13269) (7119.15532 8022.24740) (7117.27002 8020.36199)))
("SF_SOLAR" 1 ((7117.27002 8048.64253) (7119.15532 8050.52794) (7121.04072 8048.64253) (7119.15532 8046.75713)))
("SF_SOLAR" 1 ((7117.27002 8031.67421) (7119.15532 8033.55962) (7121.04072 8031.67421) (7119.15532 8029.78880)))
("SF_ARCHITECTURE" 1 ((7117.27025 4392.38778) (7105.13224 4385.36595) (7096.53088 4370.28699) (7096.53088 3846.15385)
(7104.22704 3837.09559) (7126.54219 3839.81663) (7134.23835 3849.92500) (7134.23835 4381.60170)))
("SF_SOLAR" 1 ((7124.81143 8150.45249) (7126.69683 8152.33790) (7128.58224 8150.45249) (7126.69683 8148.56708)))
("SF_SOLAR" 1 ((7132.35294 8197.58676) (7134.23835 8199.47206) (7136.12364 8197.58676) (7134.23835 8195.70136)))
("SF_SOLAR" 1 ((7139.89446 8133.48416) (7141.77975 8135.36957) (7143.66516 8133.48416) (7141.77975 8131.59876)))
("SF_SOLAR" 1 ((7139.89446 8048.64253) (7141.77975 8050.52794) (7143.66516 8048.64253) (7141.77975 8046.75713)))
("SF_SOLAR" 1 ((7153.09197 8180.61844) (7154.97738 8182.50373) (7156.86278 8180.61844) (7154.97738 8178.73303)))
("SF_SOLAR" 1 ((7156.86278 8105.20362) (7158.74808 8107.08903) (7160.63348 8105.20362) (7158.74808 8103.31821)))
("SF_SOLAR" 1 ((7173.83111 8084.46459) (7175.71640 8086.34989) (7177.60181 8084.46459) (7175.71640 8082.57919)))
("SF_PLANTING" 1 ((7192.68473 801.28201) (7194.57014 803.16742) (7196.45554 801.28201) (7194.57014 799.39672)))
("SF_MASONRY_AND_ARCH" 1 ((7198.34084 1050.15079) (7200.22624 1052.03620) (7202.11165 1050.15079) (7200.22624
1048.26550)))
("SF_SOLAR" 1 ((7207.76776 7926.09355) (7209.65305 7927.97885) (7211.53846 7926.09355) (7209.65305 7924.20814)))
("SF_MASONRY_AND_ARCH" 1 ((7219.07998 3403.09197) (7220.96527 3404.97738) (7222.85068 3403.09197) (7220.96527
3401.20667)))
("SF_MASONRY_AND_ARCH" 1 ((7220.96527 1981.52342) (7222.85068 1983.40871) (7224.73609 1981.52342) (7222.85068
1979.63801)))
("SF_SOLAR" 1 ((7237.93360 7914.78133) (7239.81900 7916.66663) (7241.70441 7914.78133) (7239.81900 7912.89593)))
("SF_SOLAR" 1 ((7249.24581 7882.72998) (7251.13122 7884.61538) (7253.01663 7882.72998) (7251.13122 7880.84468)))
("SF_SOLAR" 1 ((7251.13122 8225.86731) (7253.01663 8227.75260) (7254.90192 8225.86731) (7253.01663 8223.98190)))
("SF_SOLAR" 1 ((7253.01663 8050.52794) (7254.90192 8052.41324) (7256.78733 8050.52794) (7254.90192 8048.64253)))
("SF_SOLAR" 1 ((7253.01663 7869.53247) (7254.90192 7871.41776) (7256.78733 7869.53247) (7254.90192 7867.64706)))
("SF_SOLAR" 1 ((7256.78733 8031.67421) (7258.67274 8033.55962) (7260.55803 8031.67421) (7258.67274 8029.78880)))
("SF_SOLAR" 1 ((7260.55803 7958.14480) (7262.44344 7960.03020) (7264.32885 7958.14480) (7262.44344 7956.25939)))
("SF_SOLAR" 1 ((7271.87025 7941.17647) (7273.75566 7943.06188) (7275.64106 7941.17647) (7273.75566 7939.29106)))
("SF_SOLAR" 1 ((7275.64106 8174.96233) (7277.52636 8176.84762) (7279.41176 8174.96233) (7277.52636 8173.07692)))
("SF_SOLAR" 1 ((7275.64106 8048.64253) (7277.52636 8050.52794) (7279.41176 8048.64253) (7277.52636 8046.75713)))
("SF_SOLAR" 1 ((7275.64106 7869.53247) (7277.52636 7871.41776) (7279.41176 7869.53247) (7277.52636 7867.64706)))
("SF_MASONRY_AND_ARCH" 1 ((7275.64106 2062.59423) (7277.52636 2064.47964) (7279.41176 2062.59423) (7277.52636
2060.70894)))
("SF_MASONRY_AND_ARCH" 1 ((7275.64106 1463.04672) (7277.52636 1464.93213) (7279.41176 1463.04672) (7277.52636
1461.16143)))
("SF_SOLAR" 1 ((7281.29717 7931.74966) (7283.18247 7933.63495) (7285.06787 7931.74966) (7283.18247 7929.86425)))
("SF_SOLAR" 1 ((7298.26550 8152.33790) (7300.15079 8154.22319) (7302.03620 8152.33790) (7300.15079 8150.45249)))
("SF_SOLAR" 1 ((7298.26550 8048.64253) (7300.15079 8050.52794) (7302.03620 8048.64253) (7300.15079 8046.75713)))
("SF_MASONRY_AND_ARCH" 1 ((7298.26550 2222.85068) (7300.15079 2224.73609) (7302.03620 2222.85068) (7300.15079
2220.96527)))
("SF_MASONRY_AND_ARCH" 1 ((7300.15079 1972.09649) (7302.03620 1973.98190) (7303.92161 1972.09649) (7302.03620
1970.21120)))
("SF_SOLAR" 1 ((7309.57771 8178.73303) (7311.46301 8180.61844) (7313.34842 8178.73303) (7311.46301 8176.84762)))
("SF_MASONRY_AND_ARCH" 1 ((7309.57771 1593.13722) (7311.46301 1595.02262) (7313.34842 1593.13722) (7311.46301
1591.25192)))
("SF_SOLAR" 1 ((7317.11912 8120.28654) (7319.00452 8122.17195) (7320.88993 8120.28654) (7319.00452 8118.40124)))
("SF_SOLAR" 1 ((7320.88993 8050.52794) (7322.77523 8052.41324) (7324.66063 8050.52794) (7322.77523 8048.64253)))
("SF_SOLAR" 1 ((7320.88993 7886.50079) (7322.77523 7888.38609) (7324.66063 7886.50079) (7322.77523 7884.61538)))
("SF_SOLAR" 1 ((7320.88993 7875.18857) (7322.77523 7877.07387) (7324.66063 7875.18857) (7322.77523 7873.30317)))
("SF_PLANTING" 1 ((7320.88993 708.89898) (7322.77523 710.78428) (7324.66063 708.89898) (7322.77523 707.01357)))
("SF_SOLAR" 1 ((7335.97285 8216.44038) (7337.85826 8218.32579) (7339.74355 8216.44038) (7337.85826 8214.55509)))
("SF_SOLAR" 1 ((7337.85826 8169.30622) (7339.74355 8171.19152) (7341.62896 8169.30622) (7339.74355 8167.42081)))
("SF_SOLAR" 1 ((7343.51437 8050.52794) (7345.39966 8052.41324) (7347.28507 8050.52794) (7345.39966 8048.64253)))
("SF_SOLAR" 1 ((7343.51437 7992.08145) (7345.39966 7993.96686) (7347.28507 7992.08145) (7345.39966 7990.19604)))
("SF_SOLAR" 1 ((7343.51437 7980.76923) (7345.39966 7982.65464) (7347.28507 7980.76923) (7345.39966 7978.88382)))
("SF_SOLAR" 1 ((7343.51437 7875.18857) (7345.39966 7877.07387) (7347.28507 7875.18857) (7345.39966 7873.30317)))
("SF_MASONRY_AND_ARCH" 1 ((7347.28507 959.65305) (7349.17048 961.53846) (7351.05577 959.65305) (7349.17048 957.76776)))
("SF_SOLAR" 1 ((7349.17048 8146.68179) (7351.05577 8148.56708) (7352.94118 8146.68179) (7351.05577 8144.79638)))
("SF_SOLAR" 1 ((7351.05577 8195.70136) (7352.94118 8197.58676) (7354.82658 8195.70136) (7352.94118 8193.81595)))
("SF_SOLAR" 1 ((7362.36799 8174.96233) (7364.25339 8176.84762) (7366.13880 8174.96233) (7364.25339 8173.07692)))
("SF_SOLAR" 1 ((7362.36799 8131.59876) (7364.25339 8133.48416) (7366.13880 8131.59876) (7364.25339 8129.71346)))
("SF_SOLAR" 1 ((7366.13880 8029.78880) (7368.02410 8031.67421) (7369.90950 8029.78880) (7368.02410 8027.90351)))
("SF_SOLAR" 1 ((7371.79491 8112.74514) (7373.68020 8114.63043) (7375.56561 8112.74514) (7373.68020 8110.85973)))
("SF_SOLAR" 1 ((7373.68020 8159.87930) (7375.56561 8161.76471) (7377.45102 8159.87930) (7375.56561 8157.99400)))
("SF_SOLAR" 1 ((7384.99242 8142.91097) (7386.87783 8144.79638) (7388.76324 8142.91097) (7386.87783 8141.02568)))
("SF_SOLAR" 1 ((7388.76324 8020.36199) (7390.64853 8022.24740) (7392.53394 8020.36199) (7390.64853 8018.47658)))
("SF_SOLAR" 1 ((7396.30464 8125.94265) (7398.19005 8127.82805) (7400.07545 8125.94265) (7398.19005 8124.05735)))
("SF_SOLAR" 1 ((7407.61686 8107.08903) (7409.50226 8108.97432) (7411.38767 8107.08903) (7409.50226 8105.20362)))
("SF_SOLAR" 1 ((7411.38767 7926.09355) (7413.27296 7927.97885) (7415.15837 7926.09355) (7413.27296 7924.20814)))
("SF_SOLAR" 1 ((7415.15837 7892.15690) (7417.04378 7894.04219) (7418.92907 7892.15690) (7417.04378 7890.27149)))
("SF_SOLAR" 1 ((7418.92907 8090.12070) (7420.81448 8092.00600) (7422.69989 8090.12070) (7420.81448 8088.23529)))
("SF_MASONRY_AND_ARCH" 1 ((7426.47059 1693.06188) (7428.35600 1694.94717) (7430.24129 1693.06188) (7428.35600
1691.17647)))
("SF_SOLAR" 1 ((7430.24129 8073.15238) (7432.12670 8075.03767) (7434.01210 8073.15238) (7432.12670 8071.26697)))
("SF_SOLAR" 1 ((7441.55351 8056.18405) (7443.43891 8058.06934) (7445.32432 8056.18405) (7443.43891 8054.29864)))
("SF_SOLAR" 1 ((7449.09502 7982.65464) (7450.98043 7984.53993) (7452.86572 7982.65464) (7450.98043 7980.76923)))
("SF_SOLAR" 1 ((7452.86572 8037.33032) (7454.75113 8039.21572) (7456.63654 8037.33032) (7454.75113 8035.44491)))
("SF_SOLAR" 1 ((7456.63654 7886.50079) (7458.52183 7888.38609) (7460.40724 7886.50079) (7458.52183 7884.61538)))
("SF_SOLAR" 1 ((7464.17794 8024.13269) (7466.06335 8026.01810) (7467.94876 8024.13269) (7466.06335 8022.24740)))
("SF_SOLAR" 1 ((7475.49016 8005.27907) (7477.37557 8007.16437) (7479.26097 8005.27907) (7477.37557 8003.39367)))
("SF_SOLAR" 1 ((7475.49016 7960.03020) (7477.37557 7961.91550) (7479.26097 7960.03020) (7477.37557 7958.14480)))
("SF_SOLAR" 1 ((7486.80238 7990.19604) (7488.68778 7992.08145) (7490.57319 7990.19604) (7488.68778 7988.31075)))
("SF_SOLAR" 1 ((7498.11459 7973.22771) (7500.00000 7975.11312) (7501.88541 7973.22771) (7500.00000 7971.34242)))
("SF_SOLAR" 1 ((7498.11459 7886.50079) (7500.00000 7888.38609) (7501.88541 7886.50079) (7500.00000 7884.61538)))
("SF_SOLAR" 1 ((7498.11459 7875.18857) (7500.00000 7877.07387) (7501.88541 7875.18857) (7500.00000 7873.30317)))
("SF_SOLAR" 1 ((7513.19762 7960.03020) (7515.08292 7961.91550) (7516.96833 7960.03020) (7515.08292 7958.14480)))
("SF_ARCHITECTURE" 1 ((7518.85396 4173.89853) (7511.46686 4170.28303) (7503.77070 4162.89593) (7503.77070 4117.64706)
(7503.77070 3842.38959) (7503.77070 3836.04615) (7515.08269 3834.84785) (7526.24027 3836.04615) (7530.15928 3846.15385)
(7530.15928 4159.12477) (7526.24027 4170.28303)))
("SF_SOLAR" 1 ((7520.73903 7944.94717) (7522.62443 7946.83258) (7524.50984 7944.94717) (7522.62443 7943.06188)))
("SF_PLANTING" 1 ((7524.50984 697.58676) (7526.39514 699.47206) (7528.28054 697.58676) (7526.39514 695.70136)))
("SF_SOLAR" 1 ((7535.82206 7929.86425) (7537.70735 7931.74966) (7539.59276 7929.86425) (7537.70735 7927.97885)))
("SF_SOLAR" 1 ((7535.82206 7873.30317) (7537.70735 7875.18857) (7539.59276 7873.30317) (7537.70735 7871.41776)))
("SF_SOLAR" 1 ((7543.36346 7914.78133) (7545.24887 7916.66663) (7547.13428 7914.78133) (7545.24887 7912.89593)))
("SF_SOLAR" 1 ((7554.67568 7895.92760) (7556.56109 7897.81301) (7558.44649 7895.92760) (7556.56109 7894.04219)))
("SF_ARCHITECTURE" 1 ((7586.72704 5757.91855) (7588.61233 5759.80396) (7590.49774 5757.91855) (7588.61233 5756.03314)))
("SF_SOLAR" 1 ((7667.79785 8165.53541) (7669.68326 8167.42081) (7671.56867 8165.53541) (7669.68326 8163.65011)))
("SF_MASONRY_AND_ARCH" 1 ((7671.56867 1542.23224) (7673.45396 1544.11765) (7675.33937 1542.23224) (7673.45396
1540.34695)))
("SF_SOLAR" 1 ((7677.22477 8186.27455) (7679.11007 8188.15984) (7680.99548 8186.27455) (7679.11007 8184.38914)))
("SF_SOLAR" 1 ((7682.88088 7877.07387) (7684.76618 7878.95928) (7686.65158 7877.07387) (7684.76618 7875.18857)))
("SF_SOLAR" 1 ((7682.88088 7848.79333) (7684.76618 7850.67873) (7686.65158 7848.79333) (7684.76618 7846.90803)))
("SF_MASONRY_AND_ARCH" 1 ((7697.96380 1742.08145) (7699.84921 1743.96686) (7701.73450 1742.08145) (7699.84921
1740.19604)))
("SF_PLANTING" 1 ((7701.73450 648.56708) (7703.61991 650.45249) (7705.50532 648.56708) (7703.61991 646.68179)))
("SF_SOLAR" 1 ((7711.16143 8141.02568) (7713.04672 8142.91097) (7714.93213 8141.02568) (7713.04672 8139.14027)))
("SF_SOLAR" 1 ((7720.58824 8122.17195) (7722.47364 8124.05735) (7724.35894 8122.17195) (7722.47364 8120.28654)))
("SF_MASONRY_AND_ARCH" 1 ((7722.47364 1376.31980) (7724.35894 1378.20509) (7726.24434 1376.31980) (7724.35894
1374.43439)))
("SF_SOLAR" 1 ((7726.24434 8093.89140) (7728.12975 8095.77681) (7730.01505 8093.89140) (7728.12975 8092.00600)))
("SF_SOLAR" 1 ((7731.90045 8174.96233) (7733.78586 8176.84762) (7735.67115 8174.96233) (7733.78586 8173.07692)))
("SF_SOLAR" 1 ((7735.67115 8110.85973) (7737.55656 8112.74514) (7739.44197 8110.85973) (7737.55656 8108.97432)))
("SF_SOLAR" 1 ((7746.98337 8095.77681) (7748.86878 8097.66210) (7750.75419 8095.77681) (7748.86878 8093.89140)))
("SF_MASONRY_AND_ARCH" 1 ((7748.86878 3240.95023) (7750.75419 3242.83563) (7752.63948 3240.95023) (7750.75419
3239.06482)))
("SF_PLANTING" 1 ((7752.63948 518.47658) (7754.52489 520.36199) (7756.41029 518.47658) (7754.52489 516.59129)))
("SF_SOLAR" 1 ((7754.52489 8076.92308) (7756.41029 8078.80848) (7758.29559 8076.92308) (7756.41029 8075.03767)))
("SF_SOLAR" 1 ((7756.41029 7873.30317) (7758.29559 7875.18857) (7760.18100 7873.30317) (7758.29559 7871.41776)))
("SF_PLANTING" 1 ((7765.83710 6806.18405) (7767.72251 6808.06934) (7769.60781 6806.18405) (7767.72251 6804.29864)))
("SF_SOLAR" 1 ((7769.60781 8065.61086) (7771.49321 8067.49627) (7773.37862 8065.61086) (7771.49321 8063.72545)))
("SF_SOLAR" 1 ((7771.49321 8118.40124) (7773.37862 8120.28654) (7775.26391 8118.40124) (7773.37862 8116.51584)))
("SF_SOLAR" 1 ((7777.14932 8052.41324) (7779.03473 8054.29864) (7780.92002 8052.41324) (7779.03473 8050.52794)))
("SF_SOLAR" 1 ((7780.92002 8103.31821) (7782.80543 8105.20362) (7784.69084 8103.31821) (7782.80543 8101.43292)))
("SF_SOLAR" 1 ((7784.69084 7873.30317) (7786.57613 7875.18857) (7788.46154 7873.30317) (7786.57613 7871.41776)))
("SF_SOLAR" 1 ((7788.46154 8031.67421) (7790.34695 8033.55962) (7792.23224 8031.67421) (7790.34695 8029.78880)))
("SF_SOLAR" 1 ((7792.23224 7943.06188) (7794.11765 7944.94717) (7796.00305 7943.06188) (7794.11765 7941.17647)))
("SF_SOLAR" 1 ((7797.88835 8107.08903) (7799.77376 8108.97432) (7801.65916 8107.08903) (7799.77376 8105.20362)))
("SF_SOLAR" 1 ((7801.65916 7969.45701) (7803.54446 7971.34242) (7805.42986 7969.45701) (7803.54446 7967.57161)))
("SF_SOLAR" 1 ((7816.74208 7873.30317) (7818.62749 7875.18857) (7820.51278 7873.30317) (7818.62749 7871.41776)))
("SF_SOLAR" 1 ((7818.62749 8150.45249) (7820.51278 8152.33790) (7822.39819 8150.45249) (7820.51278 8148.56708)))
("SF_SOLAR" 1 ((7818.62749 8054.29864) (7820.51278 8056.18405) (7822.39819 8054.29864) (7820.51278 8052.41324)))
("SF_SOLAR" 1 ((7826.16889 8058.06934) (7828.05430 8059.95475) (7829.93971 8058.06934) (7828.05430 8056.18405)))
("SF_SOLAR" 1 ((7829.93971 8131.59876) (7831.82500 8133.48416) (7833.71041 8131.59876) (7831.82500 8129.71346)))
("SF_SOLAR" 1 ((7835.59581 8027.90351) (7837.48111 8029.78880) (7839.36652 8027.90351) (7837.48111 8026.01810)))
("SF_SOLAR" 1 ((7837.48111 8118.40124) (7839.36652 8120.28654) (7841.25192 8118.40124) (7839.36652 8116.51584)))
("SF_SOLAR" 1 ((7848.79333 8027.90351) (7850.67873 8029.78880) (7852.56414 8027.90351) (7850.67873 8026.01810)))
("SF_SOLAR" 1 ((7848.79333 7954.37410) (7850.67873 7956.25939) (7852.56414 7954.37410) (7850.67873 7952.48869)))
("SF_PLANTING" 1 ((7854.44943 416.66663) (7856.33484 418.55204) (7858.22025 416.66663) (7856.33484 414.78133)))
("SF_SOLAR" 1 ((7869.53247 7926.09355) (7871.41776 7927.97885) (7873.30317 7926.09355) (7871.41776 7924.20814)))
("SF_SOLAR" 1 ((7877.07387 7971.34242) (7878.95928 7973.22771) (7880.84468 7971.34242) (7878.95928 7969.45701)))
("SF_SOLAR" 1 ((7882.72998 7980.76923) (7884.61538 7982.65464) (7886.50079 7980.76923) (7884.61538 7978.88382)))
("SF_SOLAR" 1 ((7882.72998 7914.78133) (7884.61538 7916.66663) (7886.50079 7914.78133) (7884.61538 7912.89593)))
("SF_SOLAR" 1 ((7905.35441 7946.83258) (7907.23982 7948.71799) (7909.12523 7946.83258) (7907.23982 7944.94717)))
("SF_SOLAR" 1 ((7916.66663 7933.63495) (7918.55204 7935.52036) (7920.43744 7933.63495) (7918.55204 7931.74966)))
("SF_SOLAR" 1 ((7924.20814 7899.69830) (7926.09355 7901.58371) (7927.97885 7899.69830) (7926.09355 7897.81301)))
("SF_SOLAR" 1 ((7927.97885 8195.70136) (7929.86425 8197.58676) (7931.74966 8195.70136) (7929.86425 8193.81595)))
("SF_SOLAR" 1 ((7931.74966 7980.76923) (7933.63495 7982.65464) (7935.52036 7980.76923) (7933.63495 7978.88382)))
("SF_SOLAR" 1 ((7943.06188 8041.10102) (7944.94717 8042.98643) (7946.83258 8041.10102) (7944.94717 8039.21572)))
("SF_SOLAR" 1 ((7946.83258 8005.27907) (7948.71799 8007.16437) (7950.60328 8005.27907) (7948.71799 8003.39367)))
("SF_SOLAR" 1 ((7958.14480 8080.69378) (7960.03020 8082.57919) (7961.91550 8080.69378) (7960.03020 8078.80848)))
("SF_SOLAR" 1 ((7958.14480 7894.04219) (7960.03020 7895.92760) (7961.91550 7894.04219) (7960.03020 7892.15690)))
("SF_SOLAR" 1 ((7961.91550 8010.93518) (7963.80090 8012.82048) (7965.68631 8010.93518) (7963.80090 8009.04977)))
("SF_SOLAR" 1 ((7973.22771 7877.07387) (7975.11312 7878.95928) (7976.99853 7877.07387) (7975.11312 7875.18857)))
("SF_SOLAR" 1 ((7984.53993 8184.38914) (7986.42534 8186.27455) (7988.31075 8184.38914) (7986.42534 8182.50373)))
("SF_SOLAR" 1 ((7988.31075 7980.76923) (7990.19604 7982.65464) (7992.08145 7980.76923) (7990.19604 7978.88382)))
("SF_SOLAR" 1 ((8003.39367 8195.70136) (8005.27907 8197.58676) (8007.16437 8195.70136) (8005.27907 8193.81595)))
("SF_SOLAR" 1 ((8007.16437 8133.48416) (8009.04977 8135.36957) (8010.93518 8133.48416) (8009.04977 8131.59876)))
("SF_SOLAR" 1 ((8010.93518 7961.91550) (8012.82048 7963.80090) (8014.70588 7961.91550) (8012.82048 7960.03020)))
("SF_SOLAR" 1 ((8010.93518 7937.40577) (8012.82048 7939.29106) (8014.70588 7937.40577) (8012.82048 7935.52036)))
("SF_SOLAR" 1 ((8022.24740 7982.65464) (8024.13269 7984.53993) (8026.01810 7982.65464) (8024.13269 7980.76923)))
("SF_SOLAR" 1 ((8037.33032 8073.15238) (8039.21572 8075.03767) (8041.10102 8073.15238) (8039.21572 8071.26697)))
("SF_SOLAR" 1 ((8052.41324 7878.95928) (8054.29864 7880.84468) (8056.18405 7878.95928) (8054.29864 7877.07387)))
("SF_SOLAR" 1 ((8056.18405 8133.48416) (8058.06934 8135.36957) (8059.95475 8133.48416) (8058.06934 8131.59876)))
("SF_SOLAR" 1 ((8073.15238 8033.55962) (8075.03767 8035.44491) (8076.92308 8033.55962) (8075.03767 8031.67421)))
("SF_ARCHITECTURE" 1 ((8076.92308 2126.69683) (8078.80848 2128.58224) (8080.69378 2126.69683) (8078.80848 2124.81143)))
("SF_SOLAR" 1 ((8078.80848 8152.33790) (8080.69378 8154.22319) (8082.57919 8152.33790) (8080.69378 8150.45249)))
("SF_SOLAR" 1 ((8078.80848 7922.32274) (8080.69378 7924.20814) (8082.57919 7922.32274) (8080.69378 7920.43744)))
("SF_SOLAR" 1 ((8082.57919 7933.63495) (8084.46459 7935.52036) (8086.34989 7933.63495) (8084.46459 7931.74966)))
("SF_SOLAR" 1 ((8099.54751 7990.19604) (8101.43292 7992.08145) (8103.31821 7990.19604) (8101.43292 7988.31075)))
("SF_SOLAR" 1 ((8124.05735 8152.33790) (8125.94265 8154.22319) (8127.82805 8152.33790) (8125.94265 8150.45249)))
("SF_SOLAR" 1 ((8146.68179 8197.58676) (8148.56708 8199.47206) (8150.45249 8197.58676) (8148.56708 8195.70136)))
("SF_SOLAR" 1 ((8146.68179 7935.52036) (8148.56708 7937.40577) (8150.45249 7935.52036) (8148.56708 7933.63495)))
("SF_SOLAR" 1 ((8150.45249 7894.04219) (8152.33790 7895.92760) (8154.22319 7894.04219) (8152.33790 7892.15690)))
("SF_SOLAR" 1 ((8152.33790 7880.84468) (8154.22319 7882.72998) (8156.10860 7880.84468) (8154.22319 7878.95928)))
("SF_SOLAR" 1 ((8157.99400 8152.33790) (8159.87930 8154.22319) (8161.76471 8152.33790) (8159.87930 8150.45249)))
("SF_SOLAR" 1 ((8161.76471 8122.17195) (8163.65011 8124.05735) (8165.53541 8122.17195) (8163.65011 8120.28654)))
("SF_SOLAR" 1 ((8161.76471 7867.64706) (8163.65011 7869.53247) (8165.53541 7867.64706) (8163.65011 7865.76165)))
("SF_SOLAR" 1 ((8191.93066 8176.84762) (8193.81595 8178.73303) (8195.70136 8176.84762) (8193.81595 8174.96233)))
("SF_SOLAR" 1 ((8191.93066 7935.52036) (8193.81595 7937.40577) (8195.70136 7935.52036) (8193.81595 7933.63495)))
("SF_SOLAR" 1 ((8191.93066 7926.09355) (8193.81595 7927.97885) (8195.70136 7926.09355) (8193.81595 7924.20814)))
("SF_SOLAR" 1 ((8195.70136 8046.75713) (8197.58676 8048.64253) (8199.47206 8046.75713) (8197.58676 8044.87183)))
("SF_SOLAR" 1 ((8195.70136 7960.03020) (8197.58676 7961.91550) (8199.47206 7960.03020) (8197.58676 7958.14480)))
("SF_SOLAR" 1 ((8199.47206 8195.70136) (8201.35747 8197.58676) (8203.24287 8195.70136) (8201.35747 8193.81595)))
("SF_SOLAR" 1 ((8208.89898 8044.87183) (8210.78428 8046.75713) (8212.66968 8044.87183) (8210.78428 8042.98643)))
("SF_SOLAR" 1 ((8210.78428 8152.33790) (8212.66968 8154.22319) (8214.55509 8152.33790) (8212.66968 8150.45249)))
("SF_SOLAR" 1 ((8214.55509 8069.38156) (8216.44038 8071.26697) (8218.32579 8069.38156) (8216.44038 8067.49627)))
("SF_SOLAR" 1 ((8214.55509 7937.40577) (8216.44038 7939.29106) (8218.32579 7937.40577) (8216.44038 7935.52036)))
("SF_SOLAR" 1 ((8237.17952 8080.69378) (8239.06482 8082.57919) (8240.95023 8080.69378) (8239.06482 8078.80848)))
("SF_SOLAR" 1 ((8267.34536 8141.02568) (8269.23077 8142.91097) (8271.11618 8141.02568) (8269.23077 8139.14027)))
("SF_SOLAR" 1 ((8269.23077 8180.61844) (8271.11618 8182.50373) (8273.00147 8180.61844) (8271.11618 8178.73303)))
("SF_ARCHITECTURE" 1 ((8271.11618 791.85520) (8273.00147 793.74061) (8274.88688 791.85520) (8273.00147 789.96980)))
("SF_SOLAR" 1 ((8278.65758 8141.02568) (8280.54299 8142.91097) (8282.42839 8141.02568) (8280.54299 8139.14027)))
("SF_SOLAR" 1 ((8282.42839 7937.40577) (8284.31369 7939.29106) (8286.19910 7937.40577) (8284.31369 7935.52036)))
("SF_SOLAR" 1 ((8299.39672 8101.43292) (8301.28201 8103.31821) (8303.16742 8101.43292) (8301.28201 8099.54751)))
("SF_SOLAR" 1 ((8305.05283 7926.09355) (8306.93812 7927.97885) (8308.82353 7926.09355) (8306.93812 7924.20814)))
("SF_SOLAR" 1 ((8325.79186 8056.18405) (8327.67726 8058.06934) (8329.56256 8056.18405) (8327.67726 8054.29864)))
("SF_SOLAR" 1 ((8337.10407 7935.52036) (8338.98948 7937.40577) (8340.87477 7935.52036) (8338.98948 7933.63495)))
("SF_SOLAR" 1 ((8344.64559 8027.90351) (8346.53088 8029.78880) (8348.41629 8027.90351) (8346.53088 8026.01810)))
("SF_SOLAR" 1 ((8346.53088 7927.97885) (8348.41629 7929.86425) (8350.30170 7927.97885) (8348.41629 7926.09355)))
("SF_SOLAR" 1 ((8395.55057 8174.96233) (8397.43586 8176.84762) (8399.32127 8174.96233) (8397.43586 8173.07692)))
("SF_ARCHITECTURE" 1 ((8395.55057 5165.91256) (8397.43586 5167.79785) (8399.32127 5165.91256) (8397.43586 5164.02715)))
("SF_SOLAR" 1 ((8406.86278 8114.63043) (8408.74808 8116.51584) (8410.63348 8114.63043) (8408.74808 8112.74514)))
("SF_ARCHITECTURE" 1 ((8410.63348 5177.22477) (8412.51889 5179.11007) (8414.40419 5177.22477) (8412.51889 5175.33937)))
("SF_SOLAR" 1 ((8440.79943 7960.03020) (8442.68473 7961.91550) (8444.57014 7960.03020) (8442.68473 7958.14480)))
("SF_SOLAR" 1 ((8463.42387 8152.33790) (8465.30916 8154.22319) (8467.19457 8152.33790) (8465.30916 8150.45249)))
("SF_SOLAR" 1 ((8463.42387 7960.03020) (8465.30916 7961.91550) (8467.19457 7960.03020) (8465.30916 7958.14480)))
("SF_SOLAR" 1 ((8463.42387 7924.20814) (8465.30916 7926.09355) (8467.19457 7924.20814) (8465.30916 7922.32274)))
("SF_SOLAR" 1 ((8465.30916 8176.84762) (8467.19457 8178.73303) (8469.07998 8176.84762) (8467.19457 8174.96233)))
("SF_SOLAR" 1 ((8474.73609 8195.70136) (8476.62138 8197.58676) (8478.50679 8195.70136) (8476.62138 8193.81595)))
("SF_SOLAR" 1 ((8486.04830 8150.45249) (8487.93360 8152.33790) (8489.81900 8150.45249) (8487.93360 8148.56708)))
("SF_SOLAR" 1 ((8486.04830 7937.40577) (8487.93360 7939.29106) (8489.81900 7937.40577) (8487.93360 7935.52036)))
("SF_SOLAR" 1 ((8486.04830 7926.09355) (8487.93360 7927.97885) (8489.81900 7926.09355) (8487.93360 7924.20814)))
("SF_SOLAR" 1 ((8499.24581 8229.63801) (8501.13122 8231.52342) (8503.01663 8229.63801) (8501.13122 8227.75260)))
("SF_SOLAR" 1 ((8508.67274 8039.21572) (8510.55803 8041.10102) (8512.44344 8039.21572) (8510.55803 8037.33032)))
("SF_SOLAR" 1 ((8508.67274 7939.29106) (8510.55803 7941.17647) (8512.44344 7939.29106) (8510.55803 7937.40577)))
("SF_SOLAR" 1 ((8508.67274 7926.09355) (8510.55803 7927.97885) (8512.44344 7926.09355) (8510.55803 7924.20814)))
("SF_SOLAR" 1 ((8512.44344 8073.15238) (8514.32885 8075.03767) (8516.21414 8073.15238) (8514.32885 8071.26697)))
("SF_SOLAR" 1 ((8516.21414 8080.69378) (8518.09955 8082.57919) (8519.98495 8080.69378) (8518.09955 8078.80848)))
("SF_SOLAR" 1 ((8525.64106 8174.96233) (8527.52636 8176.84762) (8529.41176 8174.96233) (8527.52636 8173.07692)))
("SF_SOLAR" 1 ((8538.83857 8156.10860) (8540.72398 8157.99400) (8542.60939 8156.10860) (8540.72398 8154.22319)))
("SF_SOLAR" 1 ((8542.60939 8227.75260) (8544.49468 8229.63801) (8546.38009 8227.75260) (8544.49468 8225.86731)))
("SF_SOLAR" 1 ((8546.38009 8165.53541) (8548.26550 8167.42081) (8550.15079 8165.53541) (8548.26550 8163.65011)))
("SF_SOLAR" 1 ((8550.15079 8131.59876) (8552.03620 8133.48416) (8553.92161 8131.59876) (8552.03620 8129.71346)))
("SF_SOLAR" 1 ((8553.92161 7937.40577) (8555.80690 7939.29106) (8557.69231 7937.40577) (8555.80690 7935.52036)))
("SF_SOLAR" 1 ((8553.92161 7922.32274) (8555.80690 7924.20814) (8557.69231 7922.32274) (8555.80690 7920.43744)))
("SF_SOLAR" 1 ((8559.57771 8142.91097) (8561.46301 8144.79638) (8563.34842 8142.91097) (8561.46301 8141.02568)))
("SF_SOLAR" 1 ((8559.57771 8112.74514) (8561.46301 8114.63043) (8563.34842 8112.74514) (8561.46301 8110.85973)))
("SF_SOLAR" 1 ((8569.00452 8120.28654) (8570.88993 8122.17195) (8572.77523 8120.28654) (8570.88993 8118.40124)))
("SF_SOLAR" 1 ((8572.77523 8084.46459) (8574.66063 8086.34989) (8576.54604 8084.46459) (8574.66063 8082.57919)))
("SF_SOLAR" 1 ((8576.54604 7939.29106) (8578.43133 7941.17647) (8580.31674 7939.29106) (8578.43133 7937.40577)))
("SF_SOLAR" 1 ((8576.54604 7924.20814) (8578.43133 7926.09355) (8580.31674 7924.20814) (8578.43133 7922.32274)))
("SF_SOLAR" 1 ((8580.31674 8195.70136) (8582.20215 8197.58676) (8584.08744 8195.70136) (8582.20215 8193.81595)))
("SF_SOLAR" 1 ((8584.08744 8099.54751) (8585.97285 8101.43292) (8587.85826 8099.54751) (8585.97285 8097.66210)))
("SF_SOLAR" 1 ((8584.08744 8065.61086) (8585.97285 8067.49627) (8587.85826 8065.61086) (8585.97285 8063.72545)))
("SF_SOLAR" 1 ((8591.62896 8180.61844) (8593.51437 8182.50373) (8595.39966 8180.61844) (8593.51437 8178.73303)))
("SF_SOLAR" 1 ((8591.62896 8073.15238) (8593.51437 8075.03767) (8595.39966 8073.15238) (8593.51437 8071.26697)))
("SF_SOLAR" 1 ((8595.39966 8039.21572) (8597.28507 8041.10102) (8599.17048 8039.21572) (8597.28507 8037.33032)))
("SF_SOLAR" 1 ((8595.39966 7935.52036) (8597.28507 7937.40577) (8599.17048 7935.52036) (8597.28507 7933.63495)))
("SF_SOLAR" 1 ((8599.17048 7926.09355) (8601.05577 7927.97885) (8602.94118 7926.09355) (8601.05577 7924.20814)))
("SF_SOLAR" 1 ((8602.94118 8044.87183) (8604.82658 8046.75713) (8606.71188 8044.87183) (8604.82658 8042.98643)))
("SF_SOLAR" 1 ((8606.71188 8012.82048) (8608.59729 8014.70588) (8610.48269 8012.82048) (8608.59729 8010.93518)))
("SF_SOLAR" 1 ((8618.02410 7990.19604) (8619.90950 7992.08145) (8621.79491 7990.19604) (8619.90950 7988.31075)))
("SF_SOLAR" 1 ((8618.02410 7867.64706) (8619.90950 7869.53247) (8621.79491 7867.64706) (8619.90950 7865.76165)))
("SF_SOLAR" 1 ((8621.79491 7858.22025) (8623.68020 7860.10554) (8625.56561 7858.22025) (8623.68020 7856.33484)))
("SF_SOLAR" 1 ((8625.56561 8005.27907) (8627.45102 8007.16437) (8629.33631 8005.27907) (8627.45102 8003.39367)))
("SF_SOLAR" 1 ((8629.33631 7967.57161) (8631.22172 7969.45701) (8633.10713 7967.57161) (8631.22172 7965.68631)))
("SF_SOLAR" 1 ((8636.87783 7873.30317) (8638.76324 7875.18857) (8640.64853 7873.30317) (8638.76324 7871.41776)))
("SF_SOLAR" 1 ((8640.64853 7941.17647) (8642.53394 7943.06188) (8644.41934 7941.17647) (8642.53394 7939.29106)))
("SF_SOLAR" 1 ((8644.41934 8046.75713) (8646.30464 8048.64253) (8648.19005 8046.75713) (8646.30464 8044.87183)))
("SF_SOLAR" 1 ((8651.96075 7952.48869) (8653.84615 7954.37410) (8655.73156 7952.48869) (8653.84615 7950.60328)))
("SF_SOLAR" 1 ((8667.04378 8152.33790) (8668.92907 8154.22319) (8670.81448 8152.33790) (8668.92907 8150.45249)))
("SF_SOLAR" 1 ((8670.81448 7914.78133) (8672.69989 7916.66663) (8674.58518 7914.78133) (8672.69989 7912.89593)))
("SF_SOLAR" 1 ((8689.66821 8152.33790) (8691.55351 8154.22319) (8693.43891 8152.33790) (8691.55351 8150.45249)))
("SF_SOLAR" 1 ((8708.52183 7939.29106) (8710.40724 7941.17647) (8712.29265 7939.29106) (8710.40724 7937.40577)))
("SF_SOLAR" 1 ((8708.52183 7877.07387) (8710.40724 7878.95928) (8712.29265 7877.07387) (8710.40724 7875.18857)))
("SF_SOLAR" 1 ((8712.29265 8174.96233) (8714.17794 8176.84762) (8716.06335 8174.96233) (8714.17794 8173.07692)))
("SF_SOLAR" 1 ((8712.29265 7926.09355) (8714.17794 7927.97885) (8716.06335 7926.09355) (8714.17794 7924.20814)))
("SF_SOLAR" 1 ((8734.91708 8174.96233) (8736.80238 8176.84762) (8738.68778 8174.96233) (8736.80238 8173.07692)))
("SF_SOLAR" 1 ((8734.91708 8152.33790) (8736.80238 8154.22319) (8738.68778 8152.33790) (8736.80238 8150.45249)))
("SF_SOLAR" 1 ((8734.91708 7941.17647) (8736.80238 7943.06188) (8738.68778 7941.17647) (8736.80238 7939.29106)))
("SF_SOLAR" 1 ((8738.68778 7869.53247) (8740.57319 7871.41776) (8742.45848 7869.53247) (8740.57319 7867.64706)))
("SF_SOLAR" 1 ((8738.68778 7858.22025) (8740.57319 7860.10554) (8742.45848 7858.22025) (8740.57319 7856.33484)))
("SF_SOLAR" 1 ((8746.22930 8195.70136) (8748.11459 8197.58676) (8750.00000 8195.70136) (8748.11459 8193.81595)))
("SF_SOLAR" 1 ((8757.54152 7941.17647) (8759.42681 7943.06188) (8761.31222 7941.17647) (8759.42681 7939.29106)))
("SF_SOLAR" 1 ((8757.54152 7922.32274) (8759.42681 7924.20814) (8761.31222 7922.32274) (8759.42681 7920.43744)))
("SF_SOLAR" 1 ((8783.93665 8107.08903) (8785.82206 8108.97432) (8787.70735 8107.08903) (8785.82206 8105.20362)))
("SF_SOLAR" 1 ((8791.47817 7967.57161) (8793.36346 7969.45701) (8795.24887 7967.57161) (8793.36346 7965.68631)))
("SF_SOLAR" 1 ((8799.01957 8039.21572) (8800.90498 8041.10102) (8802.79038 8039.21572) (8800.90498 8037.33032)))
("SF_SOLAR" 1 ((8810.33179 8129.71346) (8812.21719 8131.59876) (8814.10260 8129.71346) (8812.21719 8127.82805)))
("SF_SOLAR" 1 ((8823.52941 7877.07387) (8825.41482 7878.95928) (8827.30011 7877.07387) (8825.41482 7875.18857)))
("SF_SOLAR" 1 ((8825.41482 7937.40577) (8827.30011 7939.29106) (8829.18552 7937.40577) (8827.30011 7935.52036)))
("SF_SOLAR" 1 ((8829.18552 8178.73303) (8831.07093 8180.61844) (8832.95622 8178.73303) (8831.07093 8176.84762)))
("SF_SOLAR" 1 ((8848.03925 7939.29106) (8849.92455 7941.17647) (8851.80995 7939.29106) (8849.92455 7937.40577)))
("SF_ARCHITECTURE" 1 ((8861.23676 3874.43439) (8863.12217 3876.31980) (8865.00758 3874.43439) (8863.12217 3872.54898)))
("SF_SOLAR" 1 ((8866.89287 8014.70588) (8868.77828 8016.59129) (8870.66369 8014.70588) (8868.77828 8012.82048)))
("SF_SOLAR" 1 ((8900.82952 7948.71799) (8902.71493 7950.60328) (8904.60034 7948.71799) (8902.71493 7946.83258)))
("SF_ARCHITECTURE" 1 ((8915.91256 460.03020) (8917.79785 461.91550) (8919.68326 460.03020) (8917.79785 458.14480)))
("SF_SOLAR" 1 ((8961.16143 8174.96233) (8963.04672 8176.84762) (8964.93213 8174.96233) (8963.04672 8173.07692)))
("SF_SOLAR" 1 ((8961.16143 7941.17647) (8963.04672 7943.06188) (8964.93213 7941.17647) (8963.04672 7939.29106)))
("SF_SOLAR" 1 ((8980.01505 8195.70136) (8981.90045 8197.58676) (8983.78586 8195.70136) (8981.90045 8193.81595)))
("SF_SOLAR" 1 ((8983.78586 7939.29106) (8985.67115 7941.17647) (8987.55656 7939.29106) (8985.67115 7937.40577)))
("SF_SOLAR" 1 ((8983.78586 7927.97885) (8985.67115 7929.86425) (8987.55656 7927.97885) (8985.67115 7926.09355)))
("SF_SOLAR" 1 ((9006.41029 8046.75713) (9008.29559 8048.64253) (9010.18100 8046.75713) (9008.29559 8044.87183)))
("SF_SOLAR" 1 ((9051.65916 8182.50373) (9053.54446 8184.38914) (9055.42986 8182.50373) (9053.54446 8180.61844)))
("SF_SOLAR" 1 ((9051.65916 7926.09355) (9053.54446 7927.97885) (9055.42986 7926.09355) (9053.54446 7924.20814)))
("SF_SOLAR" 1 ((9055.42986 8195.70136) (9057.31527 8197.58676) (9059.20057 8195.70136) (9057.31527 8193.81595)))
("SF_SOLAR" 1 ((9066.74208 8073.15238) (9068.62749 8075.03767) (9070.51278 8073.15238) (9068.62749 8071.26697)))
("SF_SOLAR" 1 ((9074.28360 8084.46459) (9076.16889 8086.34989) (9078.05430 8084.46459) (9076.16889 8082.57919)))
("SF_SOLAR" 1 ((9085.59581 8178.73303) (9087.48111 8180.61844) (9089.36652 8178.73303) (9087.48111 8176.84762)))
("SF_ARCHITECTURE" 1 ((9089.36652 791.85520) (9091.25192 793.74061) (9093.13722 791.85520) (9091.25192 789.96980)))
("SF_SOLAR" 1 ((9096.90803 8152.33790) (9098.79333 8154.22319) (9100.67873 8152.33790) (9098.79333 8150.45249)))
("SF_ARCHITECTURE" 1 ((9127.07387 789.96980) (9128.95928 791.85520) (9130.84468 789.96980) (9128.95928 788.08450)))
("SF_SOLAR" 1 ((9164.78133 8014.70588) (9166.66663 8016.59129) (9168.55204 8014.70588) (9166.66663 8012.82048)))
("SF_SOLAR" 1 ((9187.40577 7939.29106) (9189.29106 7941.17647) (9191.17647 7939.29106) (9189.29106 7937.40577)))
("SF_ARCHITECTURE" 1 ((9208.14480 7404.52749) (9245.85124 7402.11538) (9260.93609 7405.72523) (9415.53450 7405.58348)
(9457.01357 7401.80611) (9472.09649 7390.64830) (9472.09649 6953.24310) (9472.09649 6943.13518) (9257.16346 6945.69480)
(9211.91459 6941.93744) (9198.03744 6949.47873) (9196.83948 7386.87783) (9198.03744 7394.41923)))
("SF_SOLAR" 1 ((9259.04977 8010.93518) (9260.93518 8012.82048) (9262.82048 8010.93518) (9260.93518 8009.04977)))
("SF_ARCHITECTURE" 1 ((9289.21572 384.61538) (9291.10102 386.50079) (9292.98643 384.61538) (9291.10102 382.72998)))
("SF_SOLAR" 1 ((9296.75713 8144.79638) (9298.64253 8146.68179) (9300.52794 8144.79638) (9298.64253 8142.91097)))
("SF_SOLAR" 1 ((9304.29864 8118.40124) (9306.18405 8120.28654) (9308.06934 8118.40124) (9306.18405 8116.51584)))
("SF_SOLAR" 1 ((9308.06934 7935.52036) (9309.95475 7937.40577) (9311.84016 7935.52036) (9309.95475 7933.63495)))
("SF_SOLAR" 1 ((9308.06934 7926.09355) (9309.95475 7927.97885) (9311.84016 7926.09355) (9309.95475 7924.20814)))
("SF_SOLAR" 1 ((9309.95475 8141.02568) (9311.84016 8142.91097) (9313.72545 8141.02568) (9311.84016 8139.14027)))
("SF_SOLAR" 1 ((9317.49627 8073.15238) (9319.38156 8075.03767) (9321.26697 8073.15238) (9319.38156 8071.26697)))
("SF_SOLAR" 1 ((9321.26697 8101.43292) (9323.15238 8103.31821) (9325.03767 8101.43292) (9323.15238 8099.54751)))
("SF_SOLAR" 1 ((9323.15238 7858.22025) (9325.03767 7860.10554) (9326.92308 7858.22025) (9325.03767 7856.33484)))
("SF_SOLAR" 1 ((9326.92308 8050.52794) (9328.80848 8052.41324) (9330.69378 8050.52794) (9328.80848 8048.64253)))
("SF_SOLAR" 1 ((9328.80848 8073.15238) (9330.69378 8075.03767) (9332.57919 8073.15238) (9330.69378 8071.26697)))
("SF_SOLAR" 1 ((9328.80848 8029.78880) (9330.69378 8031.67421) (9332.57919 8029.78880) (9330.69378 8027.90351)))
("SF_SOLAR" 1 ((9334.46459 8054.29864) (9336.34989 8056.18405) (9338.23529 8054.29864) (9336.34989 8052.41324)))
("SF_SOLAR" 1 ((9336.34989 8003.39367) (9338.23529 8005.27907) (9340.12070 8003.39367) (9338.23529 8001.50826)))
("SF_SOLAR" 1 ((9338.23529 8195.70136) (9340.12070 8197.58676) (9342.00600 8195.70136) (9340.12070 8193.81595)))
("SF_SOLAR" 1 ((9338.23529 8027.90351) (9340.12070 8029.78880) (9342.00600 8027.90351) (9340.12070 8026.01810)))
("SF_SOLAR" 1 ((9340.12070 7992.08145) (9342.00600 7993.96686) (9343.89140 7992.08145) (9342.00600 7990.19604)))
("SF_SOLAR" 1 ((9343.89140 8018.47658) (9345.77681 8020.36199) (9347.66210 8018.47658) (9345.77681 8016.59129)))
("SF_SOLAR" 1 ((9349.54751 8095.77681) (9351.43292 8097.66210) (9353.31821 8095.77681) (9351.43292 8093.89140)))
("SF_SOLAR" 1 ((9351.43292 7993.96686) (9353.31821 7995.85215) (9355.20362 7993.96686) (9353.31821 7992.08145)))
("SF_SOLAR" 1 ((9364.63043 7952.48869) (9366.51584 7954.37410) (9368.40124 7952.48869) (9366.51584 7950.60328)))
("SF_ARCHITECTURE" 1 ((9381.59876 2126.69683) (9383.48416 2128.58224) (9385.36957 2126.69683) (9383.48416 2124.81143)))
("SF_SOLAR" 1 ((9394.79638 7901.58371) (9396.68179 7903.46912) (9398.56708 7901.58371) (9396.68179 7899.69830)))
("SF_SOLAR" 1 ((9402.33790 8133.48416) (9404.22319 8135.36957) (9406.10860 8133.48416) (9404.22319 8131.59876)))
("SF_SOLAR" 1 ((9407.99400 7877.07387) (9409.87930 7878.95928) (9411.76471 7877.07387) (9409.87930 7875.18857)))
("SF_SOLAR" 1 ((9421.19152 7939.29106) (9423.07692 7941.17647) (9424.96233 7939.29106) (9423.07692 7937.40577)))
("SF_SOLAR" 1 ((9424.96233 7982.65464) (9426.84762 7984.53993) (9428.73303 7982.65464) (9426.84762 7980.76923)))
("SF_SOLAR" 1 ((9424.96233 7926.09355) (9426.84762 7927.97885) (9428.73303 7926.09355) (9426.84762 7924.20814)))
("SF_SOLAR" 1 ((9424.96233 7894.04219) (9426.84762 7895.92760) (9428.73303 7894.04219) (9426.84762 7892.15690)))
("SF_SOLAR" 1 ((9428.73303 7865.76165) (9430.61844 7867.64706) (9432.50373 7865.76165) (9430.61844 7863.87636)))
("SF_SOLAR" 1 ((9436.27455 7858.22025) (9438.15984 7860.10554) (9440.04525 7858.22025) (9438.15984 7856.33484)))
("SF_SOLAR" 1 ((9447.58676 8073.15238) (9449.47206 8075.03767) (9451.35747 8073.15238) (9449.47206 8071.26697)))
("SF_SOLAR" 1 ((9447.58676 8012.82048) (9449.47206 8014.70588) (9451.35747 8012.82048) (9449.47206 8010.93518)))
("SF_ARCHITECTURE" 1 ((9451.35747 392.15690) (9453.24287 394.04219) (9460.78428 392.15690) (9453.24287 390.27149)))
("SF_SOLAR" 1 ((9470.21120 8044.87183) (9472.09649 8046.75713) (9473.98190 8044.87183) (9472.09649 8042.98643)))
("SF_SOLAR" 1 ((9470.21120 7927.97885) (9472.09649 7929.86425) (9473.98190 7927.97885) (9472.09649 7926.09355)))
("SF_SOLAR" 1 ((9502.26244 8180.61844) (9504.14785 8182.50373) (9506.03314 8180.61844) (9504.14785 8178.73303)))
("SF_SOLAR" 1 ((9564.47964 8107.08903) (9566.36505 8108.97432) (9568.25034 8107.08903) (9566.36505 8105.20362)))
("SF_SOLAR" 1 ((9564.47964 7971.34242) (9566.36505 7973.22771) (9568.25034 7971.34242) (9566.36505 7969.45701)))
("SF_SOLAR" 1 ((9587.10407 8082.57919) (9588.98948 8084.46459) (9590.87477 8082.57919) (9588.98948 8080.69378)))
("SF_MASONRY_AND_ARCH" 1 ((9590.87477 6302.79038) (9592.76018 6304.67568) (9594.64559 6302.79038) (9592.76018
6300.90498)))
("SF_MASONRY_AND_ARCH" 1 ((9594.64559 4232.65464) (9596.53088 4234.53993) (9598.41629 4232.65464) (9596.53088
4230.76923)))
("SF_MASONRY_AND_ARCH" 1 ((9615.38462 3239.06482) (9617.27002 3240.95023) (9619.15532 3239.06482) (9617.27002
3237.17952)))
("SF_SOLAR" 1 ((9628.58224 8041.10102) (9630.46753 8042.98643) (9632.35294 8041.10102) (9630.46753 8039.21572)))
("SF_SOLAR" 1 ((9628.58224 7926.09355) (9630.46753 7927.97885) (9632.35294 7926.09355) (9630.46753 7924.20814)))
("SF_MASONRY_AND_ARCH" 1 ((9634.23835 3514.32885) (9636.12364 3516.21414) (9638.00905 3514.32885) (9636.12364
3512.44344)))
("SF_MASONRY_AND_ARCH" 1 ((9639.89446 6274.50984) (9641.77975 6276.39514) (9643.66516 6274.50984) (9641.77975
6272.62443)))
("SF_SOLAR" 1 ((9641.77975 8182.50373) (9643.66516 8184.38914) (9645.55057 8182.50373) (9643.66516 8180.61844)))
("SF_SOLAR" 1 ((9651.20667 8195.70136) (9653.09197 8197.58676) (9654.97738 8195.70136) (9653.09197 8193.81595)))
("SF_SOLAR" 1 ((9651.20667 7980.76923) (9653.09197 7982.65464) (9654.97738 7980.76923) (9653.09197 7978.88382)))
("SF_MASONRY_AND_ARCH" 1 ((9651.20667 1900.45249) (9653.09197 1902.33790) (9654.97738 1900.45249) (9653.09197
1898.56708)))
("SF_MASONRY_AND_ARCH" 1 ((9653.09197 4600.30170) (9654.97738 4602.18699) (9656.86278 4600.30170) (9654.97738
4598.41629)))
("SF_MASONRY_AND_ARCH" 1 ((9673.83111 2349.17048) (9675.71640 2351.05577) (9677.60181 2349.17048) (9675.71640
2347.28507)))
("SF_MASONRY_AND_ARCH" 1 ((9688.91403 1376.31980) (9690.79943 1378.20509) (9692.68473 1376.31980) (9690.79943
1374.43439)))
("SF_SOLAR" 1 ((9696.45554 8180.61844) (9698.34084 8182.50373) (9700.22624 8180.61844) (9698.34084 8178.73303)))
("SF_MASONRY_AND_ARCH" 1 ((9722.85068 6161.38767) (9724.73609 6163.27296) (9726.62138 6161.38767) (9724.73609
6159.50226)))
("SF_SOLAR" 1 ((9737.93360 8122.17195) (9739.81900 8124.05735) (9741.70441 8122.17195) (9739.81900 8120.28654)))
("SF_SOLAR" 1 ((9737.93360 7867.64706) (9739.81900 7869.53247) (9741.70441 7867.64706) (9739.81900 7865.76165)))
("SF_SOLAR" 1 ((9751.13122 8027.90351) (9753.01663 8029.78880) (9754.90192 8027.90351) (9753.01663 8026.01810)))
("SF_SOLAR" 1 ((9756.78733 8061.84016) (9758.67274 8063.72545) (9760.55803 8061.84016) (9758.67274 8059.95475)))
("SF_MASONRY_AND_ARCH" 1 ((9764.32885 220.58824) (9766.21414 222.47364) (9768.09955 220.58824) (9766.21414 218.70283)))
("SF_SOLAR" 1 ((9771.87025 7877.07387) (9773.75566 7878.95928) (9775.64106 7877.07387) (9773.75566 7875.18857)))
("SF_SOLAR" 1 ((9775.64106 7895.92760) (9777.52636 7897.81301) (9779.41176 7895.92760) (9777.52636 7894.04219)))
("SF_SOLAR" 1 ((9775.64106 7839.36652) (9777.52636 7841.25192) (9779.41176 7839.36652) (9777.52636 7837.48111)))
("SF_MASONRY_AND_ARCH" 1 ((9788.83857 2375.56561) (9790.72398 2377.45102) (9792.60939 2375.56561) (9790.72398
2373.68020)))
("SF_MASONRY_AND_ARCH" 1 ((9798.26550 1380.09050) (9800.15079 1381.97590) (9802.03620 1380.09050) (9800.15079
1378.20509)))
("SF_MASONRY_AND_ARCH" 1 ((9826.54604 1738.31075) (9828.43133 1740.19604) (9830.31674 1738.31075) (9828.43133
1736.42534)))
("SF_MASONRY_AND_ARCH" 1 ((9849.17048 5518.47658) (9851.05577 5520.36199) (9852.94118 5518.47658) (9851.05577
5516.59129)))
("SF_MASONRY_AND_ARCH" 1 ((9851.05577 5552.41324) (9852.94118 5554.29864) (9854.82658 5552.41324) (9852.94118
5550.52794)))
("SF_SOLAR" 1 ((9854.82658 7986.42534) (9856.71188 7988.31075) (9858.59729 7986.42534) (9856.71188 7984.53993)))
("SF_SOLAR" 1 ((9854.82658 7939.29106) (9856.71188 7941.17647) (9858.59729 7939.29106) (9856.71188 7937.40577)))
("SF_SOLAR" 1 ((9854.82658 7929.86425) (9856.71188 7931.74966) (9858.59729 7929.86425) (9856.71188 7927.97885)))
("SF_MASONRY_AND_ARCH" 1 ((9854.82658 2401.96075) (9856.71188 2403.84615) (9858.59729 2405.73156) (9856.71188
2400.07545)))
("SF_MASONRY_AND_ARCH" 1 ((9856.71188 4566.36505) (9858.59729 4568.25034) (9860.48269 4566.36505) (9858.59729
4564.47964)))
("SF_MASONRY_AND_ARCH" 1 ((9856.71188 2205.88235) (9858.59729 2207.76776) (9860.48269 2205.88235) (9858.59729
2203.99695)))
("SF_SOLAR" 1 ((9858.59729 7961.91550) (9860.48269 7963.80090) (9862.36799 7961.91550) (9860.48269 7960.03020)))
("SF_SOLAR" 1 ((9873.68020 7961.91550) (9875.56561 7963.80090) (9877.45102 7961.91550) (9875.56561 7960.03020)))
("SF_MASONRY_AND_ARCH" 1 ((9879.33631 5090.49774) (9881.22172 5092.38314) (9883.10713 5090.49774) (9881.22172
5088.61233)))
("SF_MASONRY_AND_ARCH" 1 ((9890.64853 3148.56708) (9892.53394 3150.45249) (9894.41934 3148.56708) (9892.53394
3146.68179)))
("SF_SOLAR" 1 ((9900.07545 8178.73303) (9901.96075 8180.61844) (9903.84615 8178.73303) (9901.96075 8176.84762)))
("SF_MASONRY_AND_ARCH" 1 ((9900.07545 1802.41324) (9901.96075 1804.29864) (9903.84615 1802.41324) (9901.96075
1800.52794)))
("SF_SOLAR" 1 ((9901.96075 7961.91550) (9903.84615 7963.80090) (9905.73156 7961.91550) (9903.84615 7960.03020)))
("SF_MASONRY_AND_ARCH" 1 ((9901.96075 2330.31674) (9903.84615 2332.20215) (9905.73156 2330.31674) (9903.84615
2328.43133)))
("SF_MASONRY_AND_ARCH" 1 ((9907.61686 4837.85826) (9909.50226 4839.74355) (9911.38767 4837.85826) (9909.50226
4835.97285)))
("SF_MASONRY_AND_ARCH" 1 ((9918.92907 678.73303) (9920.81448 680.61844) (9922.69989 678.73303) (9920.81448 676.84762)))
("SF_MASONRY_AND_ARCH" 1 ((9918.92907 644.79638) (9920.81448 646.68179) (9922.69989 644.79638) (9920.81448 642.91097)))
("SF_SOLAR" 1 ((9922.69989 7937.40577) (9924.58518 7939.29106) (9926.47059 7937.40577) (9924.58518 7935.52036)))
("SF_MASONRY_AND_ARCH" 1 ((9932.12670 1076.54604) (9934.01210 1078.43133) (9935.89740 1076.54604) (9934.01210
1074.66063)))
("SF_SOLAR" 1 ((9941.55351 8195.70136) (9943.43891 8197.58676) (9945.32432 8195.70136) (9943.43891 8193.81595)))
("SF_SOLAR" 1 ((9952.86572 8027.90351) (9954.75113 8029.78880) (9956.63654 8027.90351) (9954.75113 8026.01810)))
("SF_SOLAR" 1 ((9962.29265 8174.96233) (9964.17794 8176.84762) (9966.06335 8174.96233) (9964.17794 8173.07692)))
("SF_MASONRY_AND_ARCH" 1 ((9962.29265 5763.57466) (9964.17794 5765.46007) (9966.06335 5763.57466) (9964.17794
5761.68925)))
("SF_SOLAR" 1 ((9966.06335 8027.90351) (9967.94876 8029.78880) (9969.83405 8027.90351) (9967.94876 8026.01810)))
("SF_SOLAR" 1 ((9990.57319 8118.40124) (9992.45848 8120.28654) (9994.34389 8118.40124) (9992.45848 8116.51584)))
("SF_MASONRY_AND_ARCH" 1 ((9990.57319 3631.22172) (9992.45848 3633.10713) (9994.34389 3631.22172) (9992.45848
3629.33631)))
("SF_SOLAR" 1 ((9992.45848 8163.65011) (9994.34389 8165.53541) (9996.22930 8163.65011) (9994.34389 8161.76471)))
("SF_SOLAR" 1 ((9992.45848 8141.02568) (9994.34389 8142.91097) (9996.22930 8141.02568) (9994.34389 8139.14027)))
("SF_SOLAR" 1 ((9992.45848 8092.00600) (9994.34389 8093.89140) (9996.22930 8092.00600) (9994.34389 8090.12070)))
("SF_SOLAR" 1 ((9996.22930 8197.58676) (9998.11459 8199.47206) (10000.00000 8197.58676) (9998.11459 8195.70136)))
("SF_SOLAR" 1 ((9996.22930 7960.03020) (9998.11459 7961.91550) (10000.00000 7960.03020) (9998.11459 7958.14480)))
("SF_SOLAR" 1 ((9998.11459 7937.40577) (10000.00000 7939.29106) (10001.88541 7937.40577) (10000.00000 7935.52036)))
("SF_MASONRY_AND_ARCH" 1 ((10000.00000 2153.09197) (10001.88541 2154.97738) (10003.77070 2153.09197) (10001.88541
2151.20667)))
("SF_SOLAR" 1 ((10013.19762 7854.44943) (10015.08292 7856.33484) (10016.96833 7854.44943) (10015.08292 7852.56414)))
("SF_SOLAR" 1 ((10020.73903 8027.90351) (10022.62443 8029.78880) (10024.50984 8027.90351) (10022.62443 8026.01810)))
("SF_SOLAR" 1 ((10028.28054 8095.77681) (10030.16595 8097.66210) (10032.05124 8095.77681) (10030.16595 8093.89140)))
("SF_SOLAR" 1 ((10030.16595 8027.90351) (10032.05124 8029.78880) (10033.93665 8027.90351) (10032.05124 8026.01810)))
("SF_SOLAR" 1 ((10039.59276 8195.70136) (10041.47817 8197.58676) (10043.36346 8195.70136) (10041.47817 8193.81595)))
("SF_MASONRY_AND_ARCH" 1 ((10039.59276 2098.41629) (10041.47817 2100.30170) (10043.36346 2098.41629) (10041.47817
2096.53088)))
("SF_SOLAR" 1 ((10052.79038 8110.85973) (10054.67568 8112.74514) (10056.56109 8110.85973) (10054.67568 8108.97432)))
("SF_SOLAR" 1 ((10058.44649 7895.92760) (10060.33179 7897.81301) (10062.21719 7895.92760) (10060.33179 7894.04219)))
("SF_SOLAR" 1 ((10103.69536 8152.33790) (10105.58066 8154.22319) (10107.46606 8152.33790) (10105.58066 8150.45249)))
("SF_MASONRY_AND_ARCH" 1 ((10120.66369 950.22624) (10122.54898 952.11165) (10124.43439 950.22624) (10122.54898
948.34084)))
("SF_SOLAR" 1 ((10126.31980 8180.61844) (10128.20509 8182.50373) (10130.09050 8180.61844) (10128.20509 8178.73303)))
("SF_SOLAR" 1 ((10126.31980 8152.33790) (10128.20509 8154.22319) (10130.09050 8152.33790) (10128.20509 8150.45249)))
("SF_MASONRY_AND_ARCH" 1 ((10128.20509 1048.26550) (10130.09050 1050.15079) (10131.97590 1048.26550) (10130.09050
1046.38009)))
("SF_SOLAR" 1 ((10133.86120 7971.34242) (10135.74661 7973.22771) (10137.63201 7971.34242) (10135.74661 7969.45701)))
("SF_MASONRY_AND_ARCH" 1 ((10137.63201 5011.31222) (10139.51731 5013.19762) (10141.40271 5011.31222) (10139.51731
5009.42681)))
("SF_SOLAR" 1 ((10148.94423 8178.73303) (10150.82952 8180.61844) (10152.71493 8178.73303) (10150.82952 8176.84762)))
("SF_SOLAR" 1 ((10148.94423 8152.33790) (10150.82952 8154.22319) (10152.71493 8152.33790) (10150.82952 8150.45249)))
("SF_SOLAR" 1 ((10148.94423 7895.92760) (10150.82952 7897.81301) (10152.71493 7895.92760) (10150.82952 7894.04219)))
("SF_MASONRY_AND_ARCH" 1 ((10150.82952 1595.02262) (10152.71493 1596.90803) (10154.60034 1595.02262) (10152.71493
1593.13722)))
("SF_MASONRY_AND_ARCH" 1 ((10160.25645 3240.95023) (10162.14174 3242.83563) (10164.02715 3240.95023) (10162.14174
3239.06482)))
("SF_MASONRY_AND_ARCH" 1 ((10169.68326 822.02115) (10171.56867 823.90645) (10173.45396 822.02115) (10171.56867
820.13575)))
("SF_SOLAR" 1 ((10171.56867 8180.61844) (10173.45396 8182.50373) (10175.33937 8180.61844) (10173.45396 8178.73303)))
("SF_SOLAR" 1 ((10175.33937 8195.70136) (10177.22477 8197.58676) (10179.11007 8195.70136) (10177.22477 8193.81595)))
("SF_SOLAR" 1 ((10182.88088 7894.04219) (10184.76618 7895.92760) (10186.65158 7894.04219) (10184.76618 7892.15690)))
("SF_MASONRY_AND_ARCH" 1 ((10194.19310 5211.16143) (10196.07839 5213.04672) (10197.96380 5211.16143) (10196.07839
5209.27602)))
("SF_MASONRY_AND_ARCH" 1 ((10194.19310 822.02115) (10196.07839 823.90645) (10197.96380 822.02115) (10196.07839
820.13575)))
("SF_MASONRY_AND_ARCH" 1 ((10216.81753 416.66663) (10218.70283 418.55204) (10220.58824 416.66663) (10218.70283
414.78133)))
("SF_SOLAR" 1 ((10218.70283 7877.07387) (10220.58824 7878.95928) (10222.47364 7877.07387) (10220.58824 7875.18857)))
("SF_MASONRY_AND_ARCH" 1 ((10228.12975 1383.86120) (10230.01505 1385.74661) (10231.90045 1383.86120) (10230.01505
1381.97590)))
("SF_SOLAR" 1 ((10239.44197 8182.50373) (10241.32726 8184.38914) (10243.21267 8182.50373) (10241.32726 8180.61844)))
("SF_SOLAR" 1 ((10262.06640 8197.58676) (10263.95170 8199.47206) (10265.83710 8197.58676) (10263.95170 8195.70136)))
("SF_SOLAR" 1 ((10262.06640 8152.33790) (10263.95170 8154.22319) (10265.83710 8152.33790) (10263.95170 8150.45249)))
("SF_SOLAR" 1 ((10262.06640 7963.80090) (10263.95170 7965.68631) (10265.83710 7963.80090) (10263.95170 7961.91550)))
("SF_SOLAR" 1 ((10284.69084 8195.70136) (10286.57613 8197.58676) (10288.46154 8195.70136) (10286.57613 8193.81595)))
("SF_SOLAR" 1 ((10284.69084 8152.33790) (10286.57613 8154.22319) (10288.46154 8152.33790) (10286.57613 8150.45249)))
("SF_SOLAR" 1 ((10284.69084 7961.91550) (10286.57613 7963.80090) (10288.46154 7961.91550) (10286.57613 7960.03020)))
("SF_MASONRY_AND_ARCH" 1 ((10296.00305 2903.46912) (10297.88835 2905.35441) (10299.77376 2903.46912) (10297.88835
2901.58371)))
("SF_SOLAR" 1 ((10305.42986 7980.76923) (10307.31527 7982.65464) (10309.20057 7980.76923) (10307.31527 7978.88382)))
("SF_SOLAR" 1 ((10307.31527 8152.33790) (10309.20057 8154.22319) (10311.08597 8152.33790) (10309.20057 8150.45249)))
("SF_SOLAR" 1 ((10329.93971 8122.17195) (10331.82500 8124.05735) (10333.71041 8122.17195) (10331.82500 8120.28654)))
("SF_MASONRY_AND_ARCH" 1 ((10346.90803 2360.48269) (10348.79333 2362.36799) (10350.67873 2360.48269) (10348.79333
2358.59729)))
("SF_SOLAR" 1 ((10352.56414 8152.33790) (10354.44943 8154.22319) (10356.33484 8152.33790) (10354.44943 8150.45249)))
("SF_SOLAR" 1 ((10360.10554 8180.61844) (10361.99095 8182.50373) (10363.87636 8180.61844) (10361.99095 8178.73303)))
("SF_MASONRY_AND_ARCH" 1 ((10361.99095 3504.90192) (10363.87636 3506.78733) (10365.76165 3504.90192) (10363.87636
3503.01663)))
("SF_MASONRY_AND_ARCH" 1 ((10363.87636 5009.42681) (10365.76165 5011.31222) (10367.64706 5009.42681) (10365.76165
5007.54152)))
("SF_SOLAR" 1 ((10375.18857 7894.04219) (10377.07387 7895.92760) (10378.95928 7894.04219) (10377.07387 7892.15690)))
("SF_MASONRY_AND_ARCH" 1 ((10392.15690 3785.82206) (10394.04219 3787.70735) (10395.92760 3785.82206) (10394.04219
3783.93665)))
("SF_SOLAR" 1 ((10397.81301 7927.97885) (10399.69830 7929.86425) (10401.58371 7927.97885) (10399.69830 7926.09355)))
("SF_SOLAR" 1 ((10420.43744 8182.50373) (10422.32274 8184.38914) (10424.20814 8182.50373) (10422.32274 8180.61844)))
("SF_SOLAR" 1 ((10443.06188 7939.29106) (10444.94717 7941.17647) (10446.83258 7939.29106) (10444.94717 7937.40577)))
("SF_SOLAR" 1 ((10443.06188 7927.97885) (10444.94717 7929.86425) (10446.83258 7927.97885) (10444.94717 7926.09355)))
("SF_SOLAR" 1 ((10443.06188 7895.92760) (10444.94717 7897.81301) (10446.83258 7895.92760) (10444.94717 7894.04219)))
("SF_SOLAR" 1 ((10465.68631 8178.73303) (10467.57161 8180.61844) (10469.45701 8178.73303) (10467.57161 8176.84762)))
("SF_SOLAR" 1 ((10465.68631 8152.33790) (10467.57161 8154.22319) (10469.45701 8152.33790) (10467.57161 8150.45249)))
("SF_SOLAR" 1 ((10465.68631 7858.22025) (10467.57161 7860.10554) (10469.45701 7858.22025) (10467.57161 7856.33484)))
("SF_SOLAR" 1 ((10486.42534 7880.84468) (10488.31075 7882.72998) (10490.19604 7880.84468) (10488.31075 7878.95928)))
("SF_SOLAR" 1 ((10495.85215 7897.81301) (10497.73756 7899.69830) (10499.62296 7897.81301) (10497.73756 7895.92760)))
("SF_SOLAR" 1 ((10495.85215 7880.84468) (10497.73756 7882.72998) (10499.62296 7880.84468) (10497.73756 7878.95928)))
("SF_SOLAR" 1 ((10507.16437 7939.29106) (10509.04977 7941.17647) (10510.93518 7939.29106) (10509.04977 7937.40577)))
("SF_SOLAR" 1 ((10507.16437 7927.97885) (10509.04977 7929.86425) (10510.93518 7927.97885) (10509.04977 7926.09355)))
("SF_SOLAR" 1 ((10510.93518 8152.33790) (10512.82048 8154.22319) (10514.70588 8152.33790) (10512.82048 8150.45249)))
("SF_SOLAR" 1 ((10533.55962 8197.58676) (10535.44491 8199.47206) (10537.33032 8197.58676) (10535.44491 8195.70136)))
("SF_SOLAR" 1 ((10533.55962 8131.59876) (10535.44491 8133.48416) (10537.33032 8131.59876) (10535.44491 8129.71346)))
("SF_SOLAR" 1 ((10563.72545 7960.03020) (10565.61086 7961.91550) (10567.49627 7960.03020) (10565.61086 7958.14480)))
("SF_SOLAR" 1 ((10573.15238 8195.70136) (10575.03767 8197.58676) (10576.92308 8195.70136) (10575.03767 8193.81595)))
("SF_SOLAR" 1 ((10582.57919 8005.27907) (10584.46459 8007.16437) (10586.34989 8005.27907) (10584.46459 8003.39367)))
("SF_SOLAR" 1 ((10582.57919 7860.10554) (10584.46459 7861.99095) (10586.34989 7860.10554) (10584.46459 7858.22025)))
("SF_SOLAR" 1 ((10590.12070 7880.84468) (10592.00600 7882.72998) (10593.89140 7880.84468) (10592.00600 7878.95928)))
("SF_SOLAR" 1 ((10601.43292 8137.25486) (10603.31821 8139.14027) (10605.20362 8137.25486) (10603.31821 8135.36957)))
("SF_SOLAR" 1 ((10605.20362 7926.09355) (10607.08903 7927.97885) (10608.97432 7926.09355) (10607.08903 7924.20814)))
("SF_SOLAR" 1 ((10614.63043 7939.29106) (10616.51584 7941.17647) (10618.40124 7939.29106) (10616.51584 7937.40577)))
("SF_SOLAR" 1 ((10639.14027 8041.10102) (10641.02568 8042.98643) (10642.91097 8041.10102) (10641.02568 8039.21572)))
("SF_SOLAR" 1 ((10646.68179 8229.63801) (10648.56708 8231.52342) (10650.45249 8229.63801) (10648.56708 8227.75260)))
("SF_SOLAR" 1 ((10673.07692 8195.70136) (10674.96233 8197.58676) (10676.84762 8195.70136) (10674.96233 8193.81595)))
("SF_SOLAR" 1 ((10673.07692 8180.61844) (10674.96233 8182.50373) (10676.84762 8180.61844) (10674.96233 8178.73303)))
("SF_SOLAR" 1 ((10688.15984 8039.21572) (10690.04525 8041.10102) (10691.93066 8039.21572) (10690.04525 8037.33032)))
("SF_SOLAR" 1 ((10718.32579 7982.65464) (10720.21120 7984.53993) (10722.09649 7982.65464) (10720.21120 7980.76923)))
("SF_SOLAR" 1 ((10722.09649 7939.29106) (10723.98190 7941.17647) (10725.86731 7939.29106) (10723.98190 7937.40577)))
("SF_SOLAR" 1 ((10748.49174 8005.27907) (10750.37704 8007.16437) (10752.26244 8005.27907) (10750.37704 8003.39367)))
("SF_SOLAR" 1 ((10763.57466 8118.40124) (10765.46007 8120.28654) (10767.34536 8118.40124) (10765.46007 8116.51584)))
("SF_SOLAR" 1 ((10797.51131 7941.17647) (10799.39672 7943.06188) (10801.28201 7941.17647) (10799.39672 7939.29106)))
("SF_SOLAR" 1 ((10797.51131 7927.97885) (10799.39672 7929.86425) (10801.28201 7927.97885) (10799.39672 7926.09355)))
("SF_ARCHITECTURE" 1 ((10805.05283 460.03020) (10806.93812 461.91550) (10808.82353 460.03020) (10806.93812 458.14480)))
("SF_ARCHITECTURE" 1 ((10806.93722 7432.12670) (10814.47964 7432.12670) (10859.72851 7431.97839) (10874.80566
7427.15848) (10882.19830 7417.04367) (10881.14808 6908.00079) (10867.27093 6900.45905) (10539.22149 6905.42726)
(10528.96007 6919.30645) (10524.13869 6953.24310) (10524.13869 7386.87783) (10530.77941 7417.04400) (10546.75622
7431.97183) (10595.77771 7428.35622) (10618.40215 7432.12014) (10761.68835 7432.12014) (10791.85520 7428.35622)))
("SF_ARCHITECTURE" 1 ((10806.93812 789.96980) (10808.82353 791.85520) (10810.70894 789.96980) (10808.82353 788.08450)))
("SF_SOLAR" 1 ((10808.82353 8095.77681) (10810.70894 8097.66210) (10812.59423 8095.77681) (10810.70894 8093.89140)))
("SF_ARCHITECTURE" 1 ((10825.79186 7400.76301) (10835.89921 7390.64830) (10837.10407 7383.10735) (10837.10407
6949.47873) (10822.02206 6941.93744) (10776.77319 6945.69480) (10569.38066 6943.13518) (10559.27330 6953.24310)
(10558.07534 7198.34061) (10561.83416 7217.19457) (10563.04446 7394.41267) (10576.92308 7401.95396) (10765.46097
7401.96708) (10806.93722 7405.72523)))
("SF_SOLAR" 1 ((10827.67726 8084.46459) (10829.56256 8086.34989) (10831.44796 8084.46459) (10829.56256 8082.57919)))
("SF_SOLAR" 1 ((10827.67726 7926.09355) (10829.56256 7927.97885) (10831.44796 7926.09355) (10829.56256 7924.20814)))
("SF_SOLAR" 1 ((10850.30170 8182.50373) (10852.18699 8184.38914) (10854.07240 8182.50373) (10852.18699 8180.61844)))
("SF_SOLAR" 1 ((10872.92613 8178.73303) (10874.81143 8180.61844) (10876.69683 8178.73303) (10874.81143 8176.84762)))
("SF_SOLAR" 1 ((10880.46753 8182.50373) (10882.35294 8184.38914) (10884.23835 8182.50373) (10882.35294 8180.61844)))
("SF_ARCHITECTURE" 1 ((10904.97738 3322.02115) (10906.86278 3323.90645) (10908.74808 3322.02115) (10906.86278
3320.13575)))
("SF_SOLAR" 1 ((10925.71640 7976.99853) (10927.60181 7978.88382) (10929.48722 7976.99853) (10927.60181 7975.11312)))
("SF_SOLAR" 1 ((10929.48722 7939.29106) (10931.37251 7941.17647) (10933.25792 7939.29106) (10931.37251 7937.40577)))
("SF_ARCHITECTURE" 1 ((10935.29129 4263.50136) (10999.24491 4268.47014) (11078.43043 4268.47014) (11101.05486
4264.70588) (11481.90045 4268.47014) (11538.46154 4264.55124) (11553.54446 4257.15792) (11553.54446 4242.08145)
(11553.54446 3359.72851) (11545.99638 3344.64559) (10938.91403 3344.64559) (10931.37161 3344.64559) (10921.26425
3355.95803) (10922.62715 3393.66516) (10912.52466 3420.06007) (10912.52466 3514.32907) (10916.28337 3533.18224)
(10912.51980 3623.68066) (10916.28337 3646.30509) (10916.29581 4185.52036) (10920.21471 4238.31029)))
("SF_SOLAR" 1 ((10986.04830 8152.33790) (10987.93360 8154.22319) (10989.81900 8152.33790) (10987.93360 8150.45249)))
("SF_ARCHITECTURE" 1 ((11008.67274 5252.63948) (11010.55803 5254.52489) (11012.44344 5252.63948) (11010.55803
5250.75419)))
("SF_SOLAR" 1 ((11019.98495 7927.97885) (11021.87025 7929.86425) (11023.75566 7927.97885) (11021.87025 7926.09355)))
("SF_SOLAR" 1 ((11042.60939 7939.29106) (11044.49468 7941.17647) (11046.38009 7939.29106) (11044.49468 7937.40577)))
("SF_SOLAR" 1 ((11087.85826 7933.63495) (11089.74355 7935.52036) (11091.62896 7933.63495) (11089.74355 7931.74966)))
("SF_SOLAR" 1 ((11091.62896 8073.15238) (11093.51437 8075.03767) (11095.39966 8073.15238) (11093.51437 8071.26697)))
("SF_SOLAR" 1 ((11101.05577 8080.69378) (11102.94118 8082.57919) (11104.82658 8080.69378) (11102.94118 8078.80848)))
("SF_SOLAR" 1 ((11102.94118 8190.04525) (11104.82658 8191.93066) (11106.71188 8190.04525) (11104.82658 8188.15984)))
("SF_SOLAR" 1 ((11110.48269 8197.58676) (11112.36799 8199.47206) (11114.25339 8197.58676) (11112.36799 8195.70136)))
("SF_SOLAR" 1 ((11116.13880 7877.07387) (11118.02410 7878.95928) (11119.90950 7877.07387) (11118.02410 7875.18857)))
("SF_SOLAR" 1 ((11127.45102 7877.07387) (11129.33631 7878.95928) (11131.22172 7877.07387) (11129.33631 7875.18857)))
("SF_SOLAR" 1 ((11129.33631 8152.33790) (11131.22172 8154.22319) (11133.10713 8152.33790) (11131.22172 8150.45249)))
("SF_SOLAR" 1 ((11133.10713 8197.58676) (11134.99242 8199.47206) (11136.87783 8197.58676) (11134.99242 8195.70136)))
("SF_SOLAR" 1 ((11133.10713 8073.15238) (11134.99242 8075.03767) (11136.87783 8073.15238) (11134.99242 8071.26697)))
("SF_SOLAR" 1 ((11133.10713 8041.10102) (11134.99242 8042.98643) (11136.87783 8041.10102) (11134.99242 8039.21572)))
("SF_SOLAR" 1 ((11133.10713 7960.03020) (11134.99242 7961.91550) (11136.87783 7960.03020) (11134.99242 7958.14480)))
("SF_SOLAR" 1 ((11133.10713 7939.29106) (11134.99242 7941.17647) (11136.87783 7939.29106) (11134.99242 7937.40577)))
("SF_SOLAR" 1 ((11140.64853 7880.84468) (11142.53394 7882.72998) (11144.41934 7880.84468) (11142.53394 7878.95928)))
("SF_SOLAR" 1 ((11151.96075 7937.40577) (11153.84615 7939.29106) (11155.73156 7937.40577) (11153.84615 7935.52036)))
("SF_SOLAR" 1 ((11151.96075 7926.09355) (11153.84615 7927.97885) (11155.73156 7926.09355) (11153.84615 7924.20814)))
("SF_SOLAR" 1 ((11155.73156 8152.33790) (11157.61686 8154.22319) (11159.50226 8152.33790) (11157.61686 8150.45249)))
("SF_SOLAR" 1 ((11155.73156 8133.48416) (11157.61686 8135.36957) (11159.50226 8133.48416) (11157.61686 8131.59876)))
("SF_SOLAR" 1 ((11155.73156 8082.57919) (11157.61686 8084.46459) (11159.50226 8082.57919) (11157.61686 8080.69378)))
("SF_SOLAR" 1 ((11178.35600 8152.33790) (11180.24129 8154.22319) (11182.12670 8152.33790) (11180.24129 8150.45249)))
("SF_SOLAR" 1 ((11200.98043 8152.33790) (11202.86572 8154.22319) (11204.75113 8152.33790) (11202.86572 8150.45249)))
("SF_SOLAR" 1 ((11204.75113 7950.60328) (11206.63654 7952.48869) (11208.52183 7950.60328) (11206.63654 7948.71799)))
("SF_SOLAR" 1 ((11216.06335 7937.40577) (11217.94876 7939.29106) (11219.83405 7937.40577) (11217.94876 7935.52036)))
("SF_SOLAR" 1 ((11219.83405 7976.99853) (11221.71946 7978.88382) (11223.60486 7976.99853) (11221.71946 7975.11312)))
("SF_SOLAR" 1 ((11227.37557 7961.91550) (11229.26097 7963.80090) (11231.14627 7961.91550) (11229.26097 7960.03020)))
("SF_SOLAR" 1 ((11229.26097 8003.39367) (11231.14627 8005.27907) (11233.03167 8003.39367) (11231.14627 8001.50826)))
("SF_SOLAR" 1 ((11238.68778 7992.08145) (11240.57319 7993.96686) (11242.45848 7992.08145) (11240.57319 7990.19604)))
("SF_SOLAR" 1 ((11238.68778 7860.10554) (11240.57319 7861.99095) (11242.45848 7860.10554) (11240.57319 7858.22025)))
("SF_SOLAR" 1 ((11240.57319 8029.78880) (11242.45848 8031.67421) (11244.34389 8029.78880) (11242.45848 8027.90351)))
("SF_SOLAR" 1 ((11242.45848 8093.89140) (11244.34389 8095.77681) (11246.22930 8093.89140) (11244.34389 8092.00600)))
("SF_SOLAR" 1 ((11246.22930 8176.84762) (11248.11459 8178.73303) (11250.00000 8176.84762) (11248.11459 8174.96233)))
("SF_SOLAR" 1 ((11246.22930 7892.15690) (11248.11459 7894.04219) (11250.00000 7892.15690) (11248.11459 7890.27149)))
("SF_SOLAR" 1 ((11250.00000 8018.47658) (11251.88541 8020.36199) (11253.77070 8018.47658) (11251.88541 8016.59129)))
("SF_SOLAR" 1 ((11261.31222 7939.29106) (11263.19762 7941.17647) (11265.08292 7939.29106) (11263.19762 7937.40577)))
("SF_SOLAR" 1 ((11261.31222 7924.20814) (11263.19762 7926.09355) (11265.08292 7924.20814) (11263.19762 7922.32274)))
("SF_SOLAR" 1 ((11263.19762 8084.46459) (11265.08292 8086.34989) (11266.96833 8084.46459) (11265.08292 8082.57919)))
("SF_SOLAR" 1 ((11265.08292 8197.58676) (11266.96833 8199.47206) (11268.85373 8197.58676) (11266.96833 8195.70136)))
("SF_SOLAR" 1 ((11272.62443 8078.80848) (11274.50984 8080.69378) (11276.39514 8078.80848) (11274.50984 8076.92308)))
("SF_SOLAR" 1 ((11285.82206 8141.02568) (11287.70735 8142.91097) (11289.59276 8141.02568) (11287.70735 8139.14027)))
("SF_SOLAR" 1 ((11291.47817 7939.29106) (11293.36346 7941.17647) (11295.24887 7939.29106) (11293.36346 7937.40577)))
("SF_SOLAR" 1 ((11291.47817 7926.09355) (11293.36346 7927.97885) (11295.24887 7926.09355) (11293.36346 7924.20814)))
("SF_SOLAR" 1 ((11295.24887 8133.48416) (11297.13428 8135.36957) (11299.01957 8133.48416) (11297.13428 8131.59876)))
("SF_SOLAR" 1 ((11299.01957 8171.19152) (11300.90498 8173.07692) (11302.79038 8171.19152) (11300.90498 8169.30622)))
("SF_SOLAR" 1 ((11306.56109 8227.75260) (11308.44649 8229.63801) (11310.33179 8227.75260) (11308.44649 8225.86731)))
("SF_SOLAR" 1 ((11308.44649 8161.76471) (11310.33179 8163.65011) (11312.21719 8161.76471) (11310.33179 8159.87930)))
("SF_SOLAR" 1 ((11314.10260 7924.20814) (11315.98790 7926.09355) (11317.87330 7924.20814) (11315.98790 7922.32274)))
("SF_SOLAR" 1 ((11336.72704 7963.80090) (11338.61233 7965.68631) (11340.49774 7963.80090) (11338.61233 7961.91550)))
("SF_SOLAR" 1 ((11336.72704 7935.52036) (11338.61233 7937.40577) (11340.49774 7935.52036) (11338.61233 7933.63495)))
("SF_SOLAR" 1 ((11346.15385 8225.86731) (11348.03925 8227.75260) (11349.92455 8225.86731) (11348.03925 8223.98190)))
("SF_SOLAR" 1 ((11355.58066 8131.59876) (11357.46606 8133.48416) (11359.35147 8131.59876) (11357.46606 8129.71346)))
("SF_SOLAR" 1 ((11359.35147 8041.10102) (11361.23676 8042.98643) (11363.12217 8041.10102) (11361.23676 8039.21572)))
("SF_SOLAR" 1 ((11359.35147 7961.91550) (11361.23676 7963.80090) (11363.12217 7961.91550) (11361.23676 7960.03020)))
("SF_SOLAR" 1 ((11359.35147 7935.52036) (11361.23676 7937.40577) (11363.12217 7935.52036) (11361.23676 7933.63495)))
("SF_SOLAR" 1 ((11359.35147 7924.20814) (11361.23676 7926.09355) (11363.12217 7924.20814) (11361.23676 7922.32274)))
("SF_SOLAR" 1 ((11363.12217 8180.61844) (11365.00758 8182.50373) (11366.89287 8180.61844) (11365.00758 8178.73303)))
("SF_SOLAR" 1 ((11381.97590 8152.33790) (11383.86120 8154.22319) (11385.74661 8152.33790) (11383.86120 8150.45249)))
("SF_SOLAR" 1 ((11381.97590 7961.91550) (11383.86120 7963.80090) (11385.74661 7961.91550) (11383.86120 7960.03020)))
("SF_SOLAR" 1 ((11381.97590 7935.52036) (11383.86120 7937.40577) (11385.74661 7935.52036) (11383.86120 7933.63495)))
("SF_SOLAR" 1 ((11381.97590 7924.20814) (11383.86120 7926.09355) (11385.74661 7924.20814) (11383.86120 7922.32274)))
("SF_SOLAR" 1 ((11404.60034 8174.96233) (11406.48563 8176.84762) (11408.37104 8174.96233) (11406.48563 8173.07692)))
("SF_SOLAR" 1 ((11404.60034 8152.33790) (11406.48563 8154.22319) (11408.37104 8152.33790) (11406.48563 8150.45249)))
("SF_SOLAR" 1 ((11404.60034 7960.03020) (11406.48563 7961.91550) (11408.37104 7960.03020) (11406.48563 7958.14480)))
("SF_SOLAR" 1 ((11404.60034 7935.52036) (11406.48563 7937.40577) (11408.37104 7935.52036) (11406.48563 7933.63495)))
("SF_SOLAR" 1 ((11427.22477 8152.33790) (11429.11007 8154.22319) (11430.99548 8152.33790) (11429.11007 8150.45249)))
("SF_SOLAR" 1 ((11449.84921 8152.33790) (11451.73450 8154.22319) (11453.61991 8152.33790) (11451.73450 8150.45249)))
("SF_SOLAR" 1 ((11476.24434 7965.68631) (11478.12975 7967.57161) (11480.01505 7965.68631) (11478.12975 7963.80090)))
("SF_SOLAR" 1 ((11489.44197 7997.73756) (11491.32726 7999.62296) (11493.21267 7997.73756) (11491.32726 7995.85215)))
("SF_SOLAR" 1 ((11495.09808 8152.33790) (11496.98337 8154.22319) (11498.86878 8152.33790) (11496.98337 8150.45249)))
("SF_SOLAR" 1 ((11495.09808 8080.69378) (11496.98337 8082.57919) (11498.86878 8080.69378) (11496.98337 8078.80848)))
("SF_SOLAR" 1 ((11517.72251 8152.33790) (11519.60781 8154.22319) (11521.49321 8152.33790) (11519.60781 8150.45249)))
("SF_SOLAR" 1 ((11517.72251 8133.48416) (11519.60781 8135.36957) (11521.49321 8133.48416) (11519.60781 8131.59876)))
("SF_SOLAR" 1 ((11517.72251 7939.29106) (11519.60781 7941.17647) (11521.49321 7939.29106) (11519.60781 7937.40577)))
("SF_SOLAR" 1 ((11523.37862 8039.21572) (11525.26391 8041.10102) (11527.14932 8039.21572) (11525.26391 8037.33032)))
("SF_SOLAR" 1 ((11532.80543 8080.69378) (11534.69084 8082.57919) (11536.57613 8080.69378) (11534.69084 8078.80848)))
("SF_SOLAR" 1 ((11536.57613 8069.38156) (11538.46154 8071.26697) (11540.34695 8069.38156) (11538.46154 8067.49627)))
("SF_SOLAR" 1 ((11536.57613 8061.84016) (11538.46154 8063.72545) (11540.34695 8061.84016) (11538.46154 8059.95475)))
("SF_SOLAR" 1 ((11540.34695 7941.17647) (11542.23224 7943.06188) (11544.11765 7941.17647) (11542.23224 7939.29106)))
("SF_SOLAR" 1 ((11547.88835 8105.20362) (11549.77376 8107.08903) (11551.65916 8105.20362) (11549.77376 8103.31821)))
("SF_SOLAR" 1 ((11549.77376 8195.70136) (11551.65916 8197.58676) (11553.54446 8195.70136) (11551.65916 8193.81595)))
("SF_SOLAR" 1 ((11555.42986 8103.31821) (11557.31527 8105.20362) (11559.20057 8103.31821) (11557.31527 8101.43292)))
("SF_SOLAR" 1 ((11561.08597 8133.48416) (11562.97138 8135.36957) (11564.85667 8133.48416) (11562.97138 8131.59876)))
("SF_SOLAR" 1 ((11562.97138 7935.52036) (11564.85667 7937.40577) (11566.74208 7935.52036) (11564.85667 7933.63495)))
("SF_SOLAR" 1 ((11566.74208 8141.02568) (11568.62749 8142.91097) (11570.51278 8141.02568) (11568.62749 8139.14027)))
("SF_SOLAR" 1 ((11566.74208 8037.33032) (11568.62749 8039.21572) (11570.51278 8037.33032) (11568.62749 8035.44491)))
("SF_SOLAR" 1 ((11568.62749 8122.17195) (11570.51278 8124.05735) (11572.39819 8122.17195) (11570.51278 8120.28654)))
("SF_ARCHITECTURE" 1 ((11572.39819 4274.13269) (11574.28360 4276.01810) (11576.16889 4274.13269) (11574.28360
4272.24740)))
("SF_SOLAR" 1 ((11585.59581 8012.82048) (11587.48111 8014.70588) (11589.36652 8012.82048) (11587.48111 8010.93518)))
("SF_SOLAR" 1 ((11585.59581 7935.52036) (11587.48111 7937.40577) (11589.36652 7935.52036) (11587.48111 7933.63495)))
("SF_SOLAR" 1 ((11585.59581 7924.20814) (11587.48111 7926.09355) (11589.36652 7924.20814) (11587.48111 7922.32274)))
("SF_SOLAR" 1 ((11587.48111 8071.26697) (11589.36652 8073.15238) (11591.25192 8071.26697) (11589.36652 8069.38156)))
("SF_SOLAR" 1 ((11608.22025 8042.98643) (11610.10554 8044.87183) (11611.99095 8042.98643) (11610.10554 8041.10102)))
("SF_SOLAR" 1 ((11608.22025 7937.40577) (11610.10554 7939.29106) (11611.99095 7937.40577) (11610.10554 7935.52036)))
("SF_SOLAR" 1 ((11610.10554 8120.28654) (11611.99095 8122.17195) (11613.87636 8120.28654) (11611.99095 8118.40124)))
("SF_SOLAR" 1 ((11611.99095 8182.50373) (11613.87636 8184.38914) (11615.76165 8182.50373) (11613.87636 8180.61844)))
("SF_SOLAR" 1 ((11634.61538 7926.09355) (11636.50079 7927.97885) (11638.38609 7926.09355) (11636.50079 7924.20814)))
("SF_SOLAR" 1 ((11642.15690 7937.40577) (11644.04219 7939.29106) (11645.92760 7937.40577) (11644.04219 7935.52036)))
("SF_SOLAR" 1 ((11653.46912 7894.04219) (11655.35441 7895.92760) (11657.23982 7894.04219) (11655.35441 7892.15690)))
("SF_SOLAR" 1 ((11672.32274 8007.16437) (11674.20814 8009.04977) (11676.09355 8007.16437) (11674.20814 8005.27907)))
("SF_SOLAR" 1 ((11672.32274 7935.52036) (11674.20814 7937.40577) (11676.09355 7935.52036) (11674.20814 7933.63495)))
("SF_SOLAR" 1 ((11672.32274 7894.04219) (11674.20814 7895.92760) (11676.09355 7894.04219) (11674.20814 7892.15690)))
("SF_SOLAR" 1 ((11672.32274 7867.64706) (11674.20814 7869.53247) (11676.09355 7867.64706) (11674.20814 7865.76165)))
("SF_ARCHITECTURE" 1 ((11676.09355 5098.03925) (11677.97885 5099.92455) (11679.86425 5098.03925) (11677.97885
5096.15385)))
("SF_SOLAR" 1 ((11681.74966 7961.91550) (11683.63495 7963.80090) (11685.52036 7961.91550) (11683.63495 7960.03020)))
("SF_SOLAR" 1 ((11706.25939 8007.16437) (11708.14480 8009.04977) (11710.03020 8007.16437) (11708.14480 8005.27907)))
("SF_ARCHITECTURE" 1 ((11721.34242 4392.91097) (11723.22771 4394.79638) (11725.11312 4392.91097) (11723.22771
4391.02568)))
("SF_SOLAR" 1 ((11736.42534 7971.34242) (11738.31075 7973.22771) (11740.19604 7971.34242) (11738.31075 7969.45701)))
("SF_SOLAR" 1 ((11743.96686 7894.04219) (11745.85215 7895.92760) (11747.73756 7894.04219) (11745.85215 7892.15690)))
("SF_SOLAR" 1 ((11743.96686 7863.87636) (11745.85215 7865.76165) (11747.73756 7863.87636) (11745.85215 7861.99095)))
("SF_SOLAR" 1 ((11747.73756 7986.42534) (11749.62296 7988.31075) (11751.50826 7986.42534) (11749.62296 7984.53993)))
("SF_SOLAR" 1 ((11760.93518 8026.01810) (11762.82048 8027.90351) (11764.70588 8026.01810) (11762.82048 8024.13269)))
("SF_SOLAR" 1 ((11760.93518 8005.27907) (11762.82048 8007.16437) (11764.70588 8005.27907) (11762.82048 8003.39367)))
("SF_SOLAR" 1 ((11766.59129 7924.20814) (11768.47658 7926.09355) (11770.36199 7924.20814) (11768.47658 7922.32274)))
("SF_SOLAR" 1 ((11766.59129 7894.04219) (11768.47658 7895.92760) (11770.36199 7894.04219) (11768.47658 7892.15690)))
("SF_SOLAR" 1 ((11770.36199 8041.10102) (11772.24740 8042.98643) (11774.13269 8041.10102) (11772.24740 8039.21572)))
("SF_SOLAR" 1 ((11770.36199 7935.52036) (11772.24740 7937.40577) (11774.13269 7935.52036) (11772.24740 7933.63495)))
("SF_SOLAR" 1 ((11772.24740 8029.78880) (11774.13269 8031.67421) (11776.01810 8029.78880) (11774.13269 8027.90351)))
("SF_SOLAR" 1 ((11781.67421 8056.18405) (11783.55962 8058.06934) (11785.44491 8056.18405) (11783.55962 8054.29864)))
("SF_SOLAR" 1 ((11796.75713 8080.69378) (11798.64253 8082.57919) (11800.52794 8080.69378) (11798.64253 8078.80848)))
("SF_SOLAR" 1 ((11796.75713 8063.72545) (11798.64253 8065.61086) (11800.52794 8063.72545) (11798.64253 8061.84016)))
("SF_SOLAR" 1 ((11796.75713 7894.04219) (11798.64253 7895.92760) (11800.52794 7894.04219) (11798.64253 7892.15690)))
("SF_SOLAR" 1 ((11808.06934 8176.84762) (11809.95475 8178.73303) (11811.84016 8176.84762) (11809.95475 8174.96233)))
("SF_SOLAR" 1 ((11808.06934 7926.09355) (11809.95475 7927.97885) (11811.84016 7926.09355) (11809.95475 7924.20814)))
("SF_SOLAR" 1 ((11811.84016 7961.91550) (11813.72545 7963.80090) (11815.61086 7961.91550) (11813.72545 7960.03020)))
("SF_SOLAR" 1 ((11811.84016 7935.52036) (11813.72545 7937.40577) (11815.61086 7935.52036) (11813.72545 7933.63495)))
("SF_SOLAR" 1 ((11823.15238 8133.48416) (11825.03767 8135.36957) (11826.92308 8133.48416) (11825.03767 8131.59876)))
("SF_SOLAR" 1 ((11828.80848 8195.70136) (11830.69378 8197.58676) (11832.57919 8195.70136) (11830.69378 8193.81595)))
("SF_SOLAR" 1 ((11830.69378 8120.28654) (11832.57919 8122.17195) (11834.46459 8120.28654) (11832.57919 8118.40124)))
("SF_SOLAR" 1 ((11834.46459 7961.91550) (11836.34989 7963.80090) (11838.23529 7961.91550) (11836.34989 7960.03020)))
("SF_SOLAR" 1 ((11838.23529 7982.65464) (11840.12070 7984.53993) (11842.00600 7982.65464) (11840.12070 7980.76923)))
("SF_SOLAR" 1 ((11842.00600 7878.95928) (11843.89140 7880.84468) (11845.77681 7878.95928) (11843.89140 7877.07387)))
("SF_SOLAR" 1 ((11864.63043 7961.91550) (11866.51584 7963.80090) (11868.40124 7961.91550) (11866.51584 7960.03020)))
("SF_SOLAR" 1 ((11879.71346 8078.80848) (11881.59876 8080.69378) (11883.48416 8078.80848) (11881.59876 8076.92308)))
("SF_SOLAR" 1 ((11898.56708 8133.48416) (11900.45249 8135.36957) (11902.33790 8133.48416) (11900.45249 8131.59876)))
("SF_SOLAR" 1 ((11898.56708 7858.22025) (11900.45249 7860.10554) (11902.33790 7858.22025) (11900.45249 7856.33484)))
("SF_SOLAR" 1 ((11902.33790 8178.73303) (11904.22319 8180.61844) (11906.10860 8178.73303) (11904.22319 8176.84762)))
("SF_SOLAR" 1 ((11902.33790 8152.33790) (11904.22319 8154.22319) (11906.10860 8152.33790) (11904.22319 8150.45249)))
("SF_SOLAR" 1 ((11902.33790 7963.80090) (11904.22319 7965.68631) (11906.10860 7963.80090) (11904.22319 7961.91550)))
("SF_SOLAR" 1 ((11913.65011 7894.04219) (11915.53541 7895.92760) (11917.42081 7894.04219) (11915.53541 7892.15690)))
("SF_SOLAR" 1 ((11924.96233 8152.33790) (11926.84762 8154.22319) (11928.73303 8152.33790) (11926.84762 8150.45249)))
("SF_SOLAR" 1 ((11924.96233 7926.09355) (11926.84762 7927.97885) (11928.73303 7926.09355) (11926.84762 7924.20814)))
("SF_SOLAR" 1 ((11930.61844 7878.95928) (11932.50373 7880.84468) (11934.38914 7878.95928) (11932.50373 7877.07387)))
("SF_SOLAR" 1 ((11936.27455 7939.29106) (11938.15984 7941.17647) (11940.04525 7939.29106) (11938.15984 7937.40577)))
("SF_SOLAR" 1 ((11957.01357 8133.48416) (11958.89898 8135.36957) (11960.78428 8133.48416) (11958.89898 8131.59876)))
("SF_SOLAR" 1 ((11958.89898 8152.33790) (11960.78428 8154.22319) (11962.66968 8152.33790) (11960.78428 8150.45249)))
("SF_ARCHITECTURE" 1 ((11958.89898 2053.16742) (11960.78428 2055.05283) (11962.66968 2053.16742) (11960.78428
2051.28201)))
("SF_SOLAR" 1 ((11962.66968 8078.80848) (11964.55509 8080.69378) (11966.44038 8078.80848) (11964.55509 8076.92308)))
("SF_SOLAR" 1 ((11966.44038 8178.73303) (11968.32579 8180.61844) (11970.21120 8178.73303) (11968.32579 8176.84762)))
("SF_SOLAR" 1 ((11966.44038 8044.87183) (11968.32579 8046.75713) (11970.21120 8044.87183) (11968.32579 8042.98643)))
("SF_SOLAR" 1 ((11966.44038 7892.15690) (11968.32579 7894.04219) (11970.21120 7892.15690) (11968.32579 7890.27149)))
("SF_SOLAR" 1 ((11972.09649 8124.05735) (11973.98190 8125.94265) (11975.86731 8124.05735) (11973.98190 8122.17195)))
("SF_SOLAR" 1 ((11973.98190 7856.33484) (11975.86731 7858.22025) (11977.75260 7856.33484) (11975.86731 7854.44943)))
("SF_SOLAR" 1 ((11977.75260 7912.89593) (11979.63801 7914.78133) (11981.52342 7912.89593) (11979.63801 7911.01052)))
("SF_SOLAR" 1 ((11979.63801 7971.34242) (11981.52342 7973.22771) (11983.40871 7971.34242) (11981.52342 7969.45701)))
("SF_SOLAR" 1 ((11981.52342 7995.85215) (11983.40871 7997.73756) (11985.29412 7995.85215) (11983.40871 7993.96686)))
("SF_SOLAR" 1 ((11989.06482 7984.53993) (11990.95023 7986.42534) (11992.83563 7984.53993) (11990.95023 7982.65464)))
("SF_SOLAR" 1 ((11996.60633 8020.36199) (11998.49174 8022.24740) (12000.37704 8020.36199) (11998.49174 8018.47658)))
("SF_SOLAR" 1 ((12000.37704 8003.39367) (12002.26244 8005.27907) (12004.14785 8003.39367) (12002.26244 8001.50826)))
("SF_SOLAR" 1 ((12004.14785 8027.90351) (12006.03314 8029.78880) (12007.91855 8027.90351) (12006.03314 8026.01810)))
("SF_SOLAR" 1 ((12004.14785 7950.60328) (12006.03314 7952.48869) (12007.91855 7950.60328) (12006.03314 7948.71799)))
("SF_SOLAR" 1 ((12009.80396 8176.84762) (12011.68925 8178.73303) (12013.57466 8176.84762) (12011.68925 8174.96233)))
("SF_SOLAR" 1 ((12015.46007 7882.72998) (12017.34536 7884.61538) (12019.23077 7882.72998) (12017.34536 7880.84468)))
("SF_SOLAR" 1 ((12023.00147 8059.95475) (12024.88688 8061.84016) (12026.77229 8059.95475) (12024.88688 8058.06934)))
("SF_SOLAR" 1 ((12024.88688 8039.21572) (12026.77229 8041.10102) (12028.65758 8039.21572) (12026.77229 8037.33032)))
("SF_SOLAR" 1 ((12030.54299 7914.78133) (12032.42839 7916.66663) (12034.31369 7914.78133) (12032.42839 7912.89593)))
("SF_SOLAR" 1 ((12034.31369 8058.06934) (12036.19910 8059.95475) (12038.08450 8058.06934) (12036.19910 8056.18405)))
("SF_SOLAR" 1 ((12039.96980 8084.46459) (12041.85520 8086.34989) (12043.74061 8084.46459) (12041.85520 8082.57919)))
("SF_SOLAR" 1 ((12045.62590 8073.15238) (12047.51131 8075.03767) (12049.39672 8073.15238) (12047.51131 8071.26697)))
("SF_SOLAR" 1 ((12045.62590 8016.59129) (12047.51131 8018.47658) (12049.39672 8016.59129) (12047.51131 8014.70588)))
("SF_SOLAR" 1 ((12045.62590 7976.99853) (12047.51131 7978.88382) (12049.39672 7976.99853) (12047.51131 7975.11312)))
("SF_SOLAR" 1 ((12053.16742 8103.31821) (12055.05283 8105.20362) (12056.93812 8103.31821) (12055.05283 8101.43292)))
("SF_SOLAR" 1 ((12056.93812 7960.03020) (12058.82353 7961.91550) (12060.70894 7960.03020) (12058.82353 7958.14480)))
("SF_SOLAR" 1 ((12058.82353 8095.77681) (12060.70894 8097.66210) (12062.59423 8095.77681) (12060.70894 8093.89140)))
("SF_SOLAR" 1 ((12058.82353 8033.55962) (12060.70894 8035.44491) (12062.59423 8033.55962) (12060.70894 8031.67421)))
("SF_SOLAR" 1 ((12060.70894 7937.40577) (12062.59423 7939.29106) (12064.47964 7937.40577) (12062.59423 7935.52036)))
("SF_SOLAR" 1 ((12066.36505 8107.08903) (12068.25034 8108.97432) (12070.13575 8107.08903) (12068.25034 8105.20362)))
("SF_SOLAR" 1 ((12068.25034 8133.48416) (12070.13575 8135.36957) (12072.02115 8133.48416) (12070.13575 8131.59876)))
("SF_SOLAR" 1 ((12068.25034 8050.52794) (12070.13575 8052.41324) (12072.02115 8050.52794) (12070.13575 8048.64253)))
("SF_SOLAR" 1 ((12068.25034 8042.98643) (12070.13575 8044.87183) (12072.02115 8042.98643) (12070.13575 8041.10102)))
("SF_SOLAR" 1 ((12072.02115 7873.30317) (12073.90645 7875.18857) (12075.79186 7873.30317) (12073.90645 7871.41776)))
("SF_SOLAR" 1 ((12077.67726 8063.72545) (12079.56256 8065.61086) (12081.44796 8063.72545) (12079.56256 8061.84016)))
("SF_SOLAR" 1 ((12079.56256 8129.71346) (12081.44796 8131.59876) (12083.33337 8129.71346) (12081.44796 8127.82805)))
("SF_SOLAR" 1 ((12088.98948 8141.02568) (12090.87477 8142.91097) (12092.76018 8141.02568) (12090.87477 8139.14027)))
("SF_SOLAR" 1 ((12102.18699 8195.70136) (12104.07240 8197.58676) (12105.95781 8195.70136) (12104.07240 8193.81595)))
("SF_SOLAR" 1 ((12107.84310 7854.44943) (12109.72851 7856.33484) (12111.61391 7854.44943) (12109.72851 7852.56414)))
("SF_SOLAR" 1 ((12107.84310 7839.36652) (12109.72851 7841.25192) (12111.61391 7839.36652) (12109.72851 7837.48111)))
("SF_SOLAR" 1 ((12111.61391 8174.96233) (12113.49921 8176.84762) (12115.38462 8174.96233) (12113.49921 8173.07692)))
("SF_SOLAR" 1 ((12113.49921 8227.75260) (12115.38462 8229.63801) (12117.27002 8227.75260) (12115.38462 8225.86731)))
("SF_SOLAR" 1 ((12113.49921 8122.17195) (12115.38462 8124.05735) (12117.27002 8122.17195) (12115.38462 8120.28654)))
("SF_SOLAR" 1 ((12121.04072 8133.48416) (12122.92613 8135.36957) (12124.81143 8133.48416) (12122.92613 8131.59876)))
("SF_MASONRY_AND_ARCH" 1 ((12143.66516 1932.50373) (12145.55057 1934.38914) (12147.43586 1932.50373) (12145.55057
1930.61844)))
("SF_SOLAR" 1 ((12147.43586 8174.96233) (12149.32127 8176.84762) (12151.20667 8174.96233) (12149.32127 8173.07692)))
("SF_SOLAR" 1 ((12147.43586 8167.42081) (12149.32127 8169.30622) (12151.20667 8167.42081) (12149.32127 8165.53541)))
("SF_SOLAR" 1 ((12154.97738 8146.68179) (12156.86278 8148.56708) (12158.74808 8146.68179) (12156.86278 8144.79638)))
("SF_SOLAR" 1 ((12164.40419 8157.99400) (12166.28959 8159.87930) (12168.17500 8157.99400) (12166.28959 8156.10860)))
("SF_MASONRY_AND_ARCH" 1 ((12198.34084 2171.94570) (12200.22624 2173.83111) (12202.11165 2171.94570) (12200.22624
2170.06029)))
("SF_MASONRY_AND_ARCH" 1 ((12260.55803 1742.08145) (12262.44344 1743.96686) (12264.32885 1742.08145) (12262.44344
1740.19604)))
("SF_SOLAR" 1 ((12300.15079 7895.92760) (12302.03620 7897.81301) (12303.92161 7895.92760) (12302.03620 7894.04219)))
("SF_SOLAR" 1 ((12309.57771 7952.48869) (12311.46301 7954.37410) (12313.34842 7952.48869) (12311.46301 7950.60328)))
("SF_SOLAR" 1 ((12313.34842 7920.43744) (12315.23382 7922.32274) (12317.11912 7920.43744) (12315.23382 7918.55204)))
("SF_PLANTING" 1 ((12317.11912 644.79638) (12319.00452 646.68179) (12320.88993 644.79638) (12319.00452 642.91097)))
("SF_MASONRY_AND_ARCH" 1 ((12319.00452 3446.45554) (12320.88993 3448.34084) (12322.77523 3446.45554) (12320.88993
3444.57014)))
("SF_SOLAR" 1 ((12320.88993 7937.40577) (12322.77523 7939.29106) (12324.66063 7937.40577) (12322.77523 7935.52036)))
("SF_PLANTING" 1 ((12320.88993 7023.00147) (12322.77523 7024.88688) (12324.66063 7023.00147) (12322.77523 7021.11618)))
("SF_SOLAR" 1 ((12332.20215 7956.25939) (12334.08744 7958.14480) (12335.97285 7956.25939) (12334.08744 7954.37410)))
("SF_PLANTING" 1 ((12332.20215 388.38609) (12334.08744 390.27149) (12335.97285 388.38609) (12334.08744 386.50079)))
("SF_SOLAR" 1 ((12354.82658 7886.50079) (12356.71188 7888.38609) (12358.59729 7886.50079) (12356.71188 7884.61538)))
("SF_SOLAR" 1 ((12358.59729 7990.19604) (12360.48269 7992.08145) (12362.36799 7990.19604) (12360.48269 7988.31075)))
("SF_SOLAR" 1 ((12369.90950 8007.16437) (12371.79491 8009.04977) (12373.68020 8007.16437) (12371.79491 8005.27907)))
("SF_SOLAR" 1 ((12381.22172 8024.13269) (12383.10713 8026.01810) (12384.99242 8024.13269) (12383.10713 8022.24740)))
("SF_SOLAR" 1 ((12392.53394 8041.10102) (12394.41934 8042.98643) (12396.30464 8041.10102) (12394.41934 8039.21572)))
("SF_SOLAR" 1 ((12403.84615 8058.06934) (12405.73156 8059.95475) (12407.61686 8058.06934) (12405.73156 8056.18405)))
("SF_SOLAR" 1 ((12403.84615 8001.50826) (12405.73156 8003.39367) (12407.61686 8001.50826) (12405.73156 7999.62296)))
("SF_SOLAR" 1 ((12415.15837 8078.80848) (12417.04378 8080.69378) (12418.92907 8078.80848) (12417.04378 8076.92308)))
("SF_MASONRY_AND_ARCH" 1 ((12420.81448 2170.06029) (12422.69989 2171.94570) (12424.58518 2170.06029) (12422.69989
2168.17500)))
("SF_SOLAR" 1 ((12422.69989 8125.94265) (12424.58518 8127.82805) (12426.47059 8125.94265) (12424.58518 8124.05735)))
("SF_MASONRY_AND_ARCH" 1 ((12422.69989 2192.68473) (12424.58518 2194.57014) (12426.47059 2192.68473) (12424.58518
2190.79943)))
("SF_SOLAR" 1 ((12426.47059 8093.89140) (12428.35600 8095.77681) (12430.24129 8093.89140) (12428.35600 8092.00600)))
("SF_SOLAR" 1 ((12437.78281 8112.74514) (12439.66821 8114.63043) (12441.55351 8112.74514) (12439.66821 8110.85973)))
("SF_SOLAR" 1 ((12441.55351 8154.22319) (12443.43891 8156.10860) (12445.32432 8154.22319) (12443.43891 8152.33790)))
("SF_SOLAR" 1 ((12449.09502 8127.82805) (12450.98043 8129.71346) (12452.86572 8127.82805) (12450.98043 8125.94265)))
("SF_SOLAR" 1 ((12454.75113 8178.73303) (12456.63654 8180.61844) (12458.52183 8178.73303) (12456.63654 8176.84762)))
("SF_SOLAR" 1 ((12456.63654 7954.37410) (12458.52183 7956.25939) (12460.40724 7954.37410) (12458.52183 7952.48869)))
("SF_SOLAR" 1 ((12460.40724 8146.68179) (12462.29265 8148.56708) (12464.17794 8146.68179) (12462.29265 8144.79638)))
("SF_SOLAR" 1 ((12469.83405 8163.65011) (12471.71946 8165.53541) (12473.60486 8163.65011) (12471.71946 8161.76471)))
("SF_SOLAR" 1 ((12475.49016 7926.09355) (12477.37557 7927.97885) (12479.26097 7926.09355) (12477.37557 7924.20814)))
("SF_SOLAR" 1 ((12479.26097 7954.37410) (12481.14627 7956.25939) (12483.03167 7954.37410) (12481.14627 7952.48869)))
("SF_SOLAR" 1 ((12479.26097 7886.50079) (12481.14627 7888.38609) (12483.03167 7886.50079) (12481.14627 7884.61538)))
("SF_SOLAR" 1 ((12483.03167 8180.61844) (12484.91708 8182.50373) (12486.80238 8180.61844) (12484.91708 8178.73303)))
("SF_SOLAR" 1 ((12483.03167 8050.52794) (12484.91708 8052.41324) (12486.80238 8050.52794) (12484.91708 8048.64253)))
("SF_SOLAR" 1 ((12492.45848 8088.23529) (12494.34389 8090.12070) (12496.22930 8088.23529) (12494.34389 8086.34989)))
("SF_ARCHITECTURE" 1 ((12492.45894 3894.86425) (12485.07127 3891.24808) (12477.37557 3883.86097) (12477.37557
3842.38959) (12484.92353 3834.99627) (12499.99310 3836.04615) (12511.31222 3846.15385) (12511.31222 3883.86097)))
("SF_SOLAR" 1 ((12498.11459 8050.52794) (12500.00000 8052.41324) (12501.88541 8050.52794) (12500.00000 8048.64253)))
("SF_SOLAR" 1 ((12520.73903 7927.97885) (12522.62443 7929.86425) (12524.50984 7927.97885) (12522.62443 7926.09355)))
("SF_SOLAR" 1 ((12524.50984 8120.28654) (12526.39514 8122.17195) (12528.28054 8120.28654) (12526.39514 8118.40124)))
("SF_SOLAR" 1 ((12524.50984 8050.52794) (12526.39514 8052.41324) (12528.28054 8050.52794) (12526.39514 8048.64253)))
("SF_SOLAR" 1 ((12524.50984 7982.65464) (12526.39514 7984.53993) (12528.28054 7982.65464) (12526.39514 7980.76923)))
("SF_MASONRY_AND_ARCH" 1 ((12533.93665 2549.01957) (12535.82206 2550.90498) (12537.70735 2549.01957) (12535.82206
2547.13428)))
("SF_SOLAR" 1 ((12535.82206 8176.84762) (12537.70735 8178.73303) (12539.59276 8176.84762) (12537.70735 8174.96233)))
("SF_SOLAR" 1 ((12547.13428 8152.33790) (12549.01957 8154.22319) (12550.90498 8152.33790) (12549.01957 8150.45249)))
("SF_SOLAR" 1 ((12547.13428 8048.64253) (12549.01957 8050.52794) (12550.90498 8048.64253) (12549.01957 8046.75713)))
("SF_SOLAR" 1 ((12558.44649 7982.65464) (12560.33179 7984.53993) (12562.21719 7982.65464) (12560.33179 7980.76923)))
("SF_SOLAR" 1 ((12562.21719 7877.07387) (12564.10260 7878.95928) (12565.98790 7877.07387) (12564.10260 7875.18857)))
("SF_MASONRY_AND_ARCH" 1 ((12565.98790 2439.66821) (12567.87330 2441.55351) (12569.75871 2439.66821) (12567.87330
2437.78281)))
("SF_SOLAR" 1 ((12569.75871 8222.09649) (12571.64400 8223.98190) (12573.52941 8222.09649) (12571.64400 8220.21120)))
("SF_SOLAR" 1 ((12569.75871 8197.58676) (12571.64400 8199.47206) (12573.52941 8197.58676) (12571.64400 8195.70136)))
("SF_SOLAR" 1 ((12569.75871 8152.33790) (12571.64400 8154.22319) (12573.52941 8152.33790) (12571.64400 8150.45249)))
("SF_SOLAR" 1 ((12569.75871 8124.05735) (12571.64400 8125.94265) (12573.52941 8124.05735) (12571.64400 8122.17195)))
("SF_SOLAR" 1 ((12569.75871 8050.52794) (12571.64400 8052.41324) (12573.52941 8050.52794) (12571.64400 8048.64253)))
("SF_SOLAR" 1 ((12569.75871 7846.90803) (12571.64400 7848.79333) (12573.52941 7846.90803) (12571.64400 7845.02262)))
("SF_SOLAR" 1 ((12577.30011 7941.17647) (12579.18552 7943.06188) (12581.07093 7941.17647) (12579.18552 7939.29106)))
("SF_SOLAR" 1 ((12581.07093 7877.07387) (12582.95622 7878.95928) (12584.84163 7877.07387) (12582.95622 7875.18857)))
("SF_SOLAR" 1 ((12588.61233 8026.01810) (12590.49774 8027.90351) (12592.38314 8026.01810) (12590.49774 8024.13269)))
("SF_SOLAR" 1 ((12592.38314 8197.58676) (12594.26844 8199.47206) (12596.15385 8197.58676) (12594.26844 8195.70136)))
("SF_SOLAR" 1 ((12592.38314 8152.33790) (12594.26844 8154.22319) (12596.15385 8152.33790) (12594.26844 8150.45249)))
("SF_SOLAR" 1 ((12592.38314 8133.48416) (12594.26844 8135.36957) (12596.15385 8133.48416) (12594.26844 8131.59876)))
("SF_SOLAR" 1 ((12592.38314 7886.50079) (12594.26844 7888.38609) (12596.15385 7886.50079) (12594.26844 7884.61538)))
("SF_SOLAR" 1 ((12607.46606 8227.75260) (12609.35147 8229.63801) (12611.23676 8227.75260) (12609.35147 8225.86731)))
("SF_SOLAR" 1 ((12615.00758 8152.33790) (12616.89287 8154.22319) (12618.77828 8152.33790) (12616.89287 8150.45249)))
("SF_SOLAR" 1 ((12615.00758 7858.22025) (12616.89287 7860.10554) (12618.77828 7858.22025) (12616.89287 7856.33484)))
("SF_MASONRY_AND_ARCH" 1 ((12615.00758 1785.44491) (12616.89287 1787.33032) (12618.77828 1785.44491) (12616.89287
1783.55962)))
("SF_SOLAR" 1 ((12620.66369 7846.90803) (12622.54898 7848.79333) (12624.43439 7846.90803) (12622.54898 7845.02262)))
("SF_SOLAR" 1 ((12622.54898 8042.98643) (12624.43439 8044.87183) (12626.31980 8042.98643) (12624.43439 8041.10102)))
("SF_MASONRY_AND_ARCH" 1 ((12630.09050 1085.97285) (12631.97590 1087.85826) (12633.86120 1085.97285) (12631.97590
1084.08744)))
("SF_SOLAR" 1 ((12635.74661 7958.14480) (12637.63201 7960.03020) (12639.51731 7958.14480) (12637.63201 7956.25939)))
("SF_MASONRY_AND_ARCH" 1 ((12635.89434 2575.56968) (12628.20509 2582.96290) (12628.20509 2598.03948) (12628.20509
2624.43439) (12628.20509 2858.22048) (12628.20509 2877.07364) (12628.20509 2899.69808) (12628.20509 3148.56686)
(12628.20509 3163.65034) (12628.20509 3242.83586) (12628.20509 3261.68903) (12628.20509 3344.64581) (12639.51776
3355.80339) (12684.75973 3355.80339) (12692.15305 3348.40939) (12692.31459 3125.94242) (12696.07195 3107.08925)
(12695.93111 3046.75690) (12692.31459 3031.67421) (12692.15305 2586.72726) (12680.99548 2575.56968)))
("SF_SOLAR" 1 ((12637.63201 8133.48416) (12639.51731 8135.36957) (12641.40271 8133.48416) (12639.51731 8131.59876)))
("SF_SOLAR" 1 ((12641.40271 7888.38609) (12643.28812 7890.27149) (12645.17342 7888.38609) (12643.28812 7886.50079)))
("SF_SOLAR" 1 ((12643.28812 8016.59129) (12645.17342 8018.47658) (12647.05882 8016.59129) (12645.17342 8014.70588)))
("SF_SOLAR" 1 ((12652.71493 8041.10102) (12654.60034 8042.98643) (12656.48563 8041.10102) (12654.60034 8039.21572)))
("SF_SOLAR" 1 ((12652.71493 7854.44943) (12654.60034 7856.33484) (12656.48563 7854.44943) (12654.60034 7852.56414)))
("SF_MASONRY_AND_ARCH" 1 ((12662.14174 995.47511) (12664.02715 997.36052) (12665.91256 995.47511) (12664.02715
993.58971)))
("SF_SOLAR" 1 ((12664.02715 7929.86425) (12665.91256 7931.74966) (12667.79785 7929.86425) (12665.91256 7927.97885)))
("SF_SOLAR" 1 ((12705.50532 7992.08145) (12707.39061 7993.96686) (12709.27602 7992.08145) (12707.39061 7990.19604)))
("SF_SOLAR" 1 ((12722.47364 8144.79638) (12724.35894 8146.68179) (12726.24434 8144.79638) (12724.35894 8142.91097)))
("SF_SOLAR" 1 ((12726.24434 7869.53247) (12728.12975 7871.41776) (12730.01505 7869.53247) (12728.12975 7867.64706)))
("SF_SOLAR" 1 ((12728.12975 8024.13269) (12730.01505 8026.01810) (12731.90045 8024.13269) (12730.01505 8022.24740)))
("SF_SOLAR" 1 ((12728.12975 7971.34242) (12730.01505 7973.22771) (12731.90045 7971.34242) (12730.01505 7969.45701)))
("SF_SOLAR" 1 ((12728.12975 7958.14480) (12730.01505 7960.03020) (12731.90045 7958.14480) (12730.01505 7956.25939)))
("SF_SOLAR" 1 ((12728.12975 7927.97885) (12730.01505 7929.86425) (12731.90045 7927.97885) (12730.01505 7926.09355)))
("SF_SOLAR" 1 ((12731.90045 8157.99400) (12733.78586 8159.87930) (12735.67115 8157.99400) (12733.78586 8156.10860)))
("SF_SOLAR" 1 ((12750.75419 8048.64253) (12752.63948 8050.52794) (12754.52489 8048.64253) (12752.63948 8046.75713)))
("SF_SOLAR" 1 ((12754.52489 7871.41776) (12756.41029 7873.30317) (12758.29559 7871.41776) (12756.41029 7869.53247)))
("SF_SOLAR" 1 ((12765.83710 7850.67873) (12767.72251 7852.56414) (12769.60781 7850.67873) (12767.72251 7848.79333)))
("SF_SOLAR" 1 ((12773.37862 8050.52794) (12775.26391 8052.41324) (12777.14932 8050.52794) (12775.26391 8048.64253)))
("SF_ARCHITECTURE" 1 ((12775.26437 3913.71753) (12767.87115 3910.10204) (12760.32873 3895.17387) (12760.33563
3842.38959) (12767.72896 3834.99627) (12782.79853 3836.04615) (12794.11765 3846.15385) (12794.11765 3898.94378)
(12782.79853 3910.10204)))
("SF_SOLAR" 1 ((12779.03473 7869.53247) (12780.92002 7871.41776) (12782.80543 7869.53247) (12780.92002 7867.64706)))
("SF_SOLAR" 1 ((12792.23224 8031.67421) (12794.11765 8033.55962) (12796.00305 8031.67421) (12794.11765 8029.78880)))
("SF_SOLAR" 1 ((12796.00305 8050.52794) (12797.88835 8052.41324) (12799.77376 8050.52794) (12797.88835 8048.64253)))
("SF_SOLAR" 1 ((12797.88835 8099.54751) (12799.77376 8101.43292) (12801.65916 8099.54751) (12799.77376 8097.66210)))
("SF_SOLAR" 1 ((12797.88835 7969.45701) (12799.77376 7971.34242) (12801.65916 7969.45701) (12799.77376 7967.57161)))
("SF_SOLAR" 1 ((12812.97138 7941.17647) (12814.85667 7943.06188) (12816.74208 7941.17647) (12814.85667 7939.29106)))
("SF_SOLAR" 1 ((12818.62749 8152.33790) (12820.51278 8154.22319) (12822.39819 8152.33790) (12820.51278 8150.45249)))
("SF_SOLAR" 1 ((12818.62749 8124.05735) (12820.51278 8125.94265) (12822.39819 8124.05735) (12820.51278 8122.17195)))
("SF_SOLAR" 1 ((12824.28360 7939.29106) (12826.16889 7941.17647) (12828.05430 7939.29106) (12826.16889 7937.40577)))
("SF_SOLAR" 1 ((12826.16889 7960.03020) (12828.05430 7961.91550) (12829.93971 7960.03020) (12828.05430 7958.14480)))
("SF_SOLAR" 1 ((12833.71041 7975.11312) (12835.59581 7976.99853) (12837.48111 7975.11312) (12835.59581 7973.22771)))
("SF_SOLAR" 1 ((12835.59581 7960.03020) (12837.48111 7961.91550) (12839.36652 7960.03020) (12837.48111 7958.14480)))
("SF_MASONRY_AND_ARCH" 1 ((12837.48111 3069.38156) (12839.36652 3071.26697) (12841.25192 3069.38156) (12839.36652
3067.49627)))
("SF_MASONRY_AND_ARCH" 1 ((12839.36652 1134.99242) (12841.25192 1136.87783) (12843.13722 1134.99242) (12841.25192
1133.10713)))
("SF_SOLAR" 1 ((12841.25192 8039.21572) (12843.13722 8041.10102) (12845.02262 8039.21572) (12843.13722 8037.33032)))
("SF_SOLAR" 1 ((12845.02262 7971.34242) (12846.90803 7973.22771) (12848.79333 7971.34242) (12846.90803 7969.45701)))
("SF_SOLAR" 1 ((12848.79333 7990.19604) (12850.67873 7992.08145) (12852.56414 7990.19604) (12850.67873 7988.31075)))
("SF_MASONRY_AND_ARCH" 1 ((12852.56414 1374.43439) (12854.44943 1376.31980) (12856.33484 1374.43439) (12854.44943
1372.54898)))
("SF_SOLAR" 1 ((12858.22025 8007.16437) (12860.10554 8009.04977) (12861.99095 8007.16437) (12860.10554 8005.27907)))
("SF_SOLAR" 1 ((12863.87636 8084.46459) (12865.76165 8086.34989) (12867.64706 8084.46459) (12865.76165 8082.57919)))
("SF_SOLAR" 1 ((12869.53247 8005.27907) (12871.41776 8007.16437) (12873.30317 8005.27907) (12871.41776 8003.39367)))
("SF_SOLAR" 1 ((12871.41776 8027.90351) (12873.30317 8029.78880) (12875.18857 8027.90351) (12873.30317 8026.01810)))
("SF_SOLAR" 1 ((12878.95928 8042.98643) (12880.84468 8044.87183) (12882.72998 8042.98643) (12880.84468 8041.10102)))
("SF_MASONRY_AND_ARCH" 1 ((12878.95928 3536.95328) (12880.84468 3538.83857) (12882.72998 3536.95328) (12880.84468
3535.06787)))
("SF_SOLAR" 1 ((12882.72998 8024.13269) (12884.61538 8026.01810) (12886.50079 8024.13269) (12884.61538 8022.24740)))
("SF_SOLAR" 1 ((12892.15690 8042.98643) (12894.04219 8044.87183) (12895.92760 8042.98643) (12894.04219 8041.10102)))
("SF_SOLAR" 1 ((12909.12523 7948.71799) (12911.01052 7950.60328) (12912.89593 7948.71799) (12911.01052 7946.83258)))
("SF_SOLAR" 1 ((12912.89593 8076.92308) (12914.78133 8078.80848) (12916.66663 8076.92308) (12914.78133 8075.03767)))
("SF_SOLAR" 1 ((12916.66663 8178.73303) (12918.55204 8180.61844) (12920.43744 8178.73303) (12918.55204 8176.84762)))
("SF_SOLAR" 1 ((12931.74966 7948.71799) (12933.63495 7950.60328) (12935.52036 7948.71799) (12933.63495 7946.83258)))
("SF_PLANTING" 1 ((12941.17647 6694.94717) (12943.06188 6696.83258) (12944.94717 6694.94717) (12943.06188 6693.06188)))
("SF_SOLAR" 1 ((12954.37410 8071.26697) (12956.25939 8073.15238) (12958.14480 8071.26697) (12956.25939 8069.38156)))
("SF_SOLAR" 1 ((12954.37410 8050.52794) (12956.25939 8052.41324) (12958.14480 8050.52794) (12956.25939 8048.64253)))
("SF_SOLAR" 1 ((12954.37410 8003.39367) (12956.25939 8005.27907) (12958.14480 8003.39367) (12956.25939 8001.50826)))
("SF_SOLAR" 1 ((12954.37410 7929.86425) (12956.25939 7931.74966) (12958.14480 7929.86425) (12956.25939 7927.97885)))
("SF_SOLAR" 1 ((12958.14480 8146.68179) (12960.03020 8148.56708) (12961.91550 8146.68179) (12960.03020 8144.79638)))
("SF_SOLAR" 1 ((12978.88382 7980.76923) (12980.76923 7982.65464) (12982.65464 7980.76923) (12980.76923 7978.88382)))
("SF_SOLAR" 1 ((12984.53993 7886.50079) (12986.42534 7888.38609) (12988.31075 7886.50079) (12986.42534 7884.61538)))
("SF_SOLAR" 1 ((12995.85215 7976.99853) (12997.73756 7978.88382) (12999.62296 7976.99853) (12997.73756 7975.11312)))
("SF_SOLAR" 1 ((12999.62296 7986.42534) (13001.50826 7988.31075) (13003.39367 7986.42534) (13001.50826 7984.53993)))
("SF_MASONRY_AND_ARCH" 1 ((12999.62296 2575.41482) (13001.50826 2577.30011) (13003.39367 2575.41482) (13001.50826
2573.52941)))
("SF_SOLAR" 1 ((13003.39367 7950.60328) (13005.27907 7952.48869) (13007.16437 7950.60328) (13005.27907 7948.71799)))
("SF_SOLAR" 1 ((13014.70588 7850.67873) (13016.59129 7852.56414) (13018.47658 7850.67873) (13016.59129 7848.79333)))
("SF_MASONRY_AND_ARCH" 1 ((13016.59129 3186.27455) (13018.47658 3188.15984) (13020.36199 3186.27455) (13018.47658
3184.38914)))
("SF_SOLAR" 1 ((13022.24740 8197.58676) (13024.13269 8199.47206) (13026.01810 8197.58676) (13024.13269 8195.70136)))
("SF_SOLAR" 1 ((13022.24740 8176.84762) (13024.13269 8178.73303) (13026.01810 8176.84762) (13024.13269 8174.96233)))
("SF_SOLAR" 1 ((13022.24740 8050.52794) (13024.13269 8052.41324) (13026.01810 8050.52794) (13024.13269 8048.64253)))
("SF_MASONRY_AND_ARCH" 1 ((13031.67421 1504.52489) (13033.55962 1506.41029) (13035.44491 1504.52489) (13033.55962
1502.63948)))
("SF_MASONRY_AND_ARCH" 1 ((13041.10102 3288.08450) (13042.98643 3289.96980) (13044.87183 3288.08450) (13042.98643
3286.19910)))
("SF_SOLAR" 1 ((13044.87183 8022.24740) (13046.75713 8024.13269) (13048.64253 8022.24740) (13046.75713 8020.36199)))
("SF_SOLAR" 1 ((13052.41324 7937.40577) (13054.29864 7939.29106) (13056.18405 7937.40577) (13054.29864 7935.52036)))
("SF_SOLAR" 1 ((13056.18405 7869.53247) (13058.06934 7871.41776) (13059.95475 7869.53247) (13058.06934 7867.64706)))
("SF_SOLAR" 1 ((13059.95475 7926.09355) (13061.84016 7927.97885) (13063.72545 7926.09355) (13061.84016 7924.20814)))
("SF_SOLAR" 1 ((13063.72545 7956.25939) (13065.61086 7958.14480) (13067.49627 7956.25939) (13065.61086 7954.37410)))
("SF_PLANTING" 1 ((13069.38156 820.13575) (13071.26697 822.02115) (13073.15238 820.13575) (13071.26697 818.25034)))
("SF_SOLAR" 1 ((13071.26697 7854.44943) (13073.15238 7856.33484) (13075.03767 7854.44943) (13073.15238 7852.56414)))
("SF_SOLAR" 1 ((13073.15238 7946.83258) (13075.03767 7948.71799) (13076.92308 7946.83258) (13075.03767 7944.94717)))
("SF_SOLAR" 1 ((13076.92308 7973.22771) (13078.80848 7975.11312) (13080.69378 7973.22771) (13078.80848 7971.34242)))
("SF_SOLAR" 1 ((13084.46459 7963.80090) (13086.34989 7965.68631) (13088.23529 7963.80090) (13086.34989 7961.91550)))
("SF_SOLAR" 1 ((13086.34989 7990.19604) (13088.23529 7992.08145) (13090.12070 7990.19604) (13088.23529 7988.31075)))
("SF_MASONRY_AND_ARCH" 1 ((13090.12070 1676.09355) (13092.00600 1677.97885) (13093.89140 1676.09355) (13092.00600
1674.20814)))
("SF_SOLAR" 1 ((13095.77681 7982.65464) (13097.66210 7984.53993) (13099.54751 7982.65464) (13097.66210 7980.76923)))
("SF_MASONRY_AND_ARCH" 1 ((13099.54751 1240.57319) (13101.43292 1242.45848) (13103.31821 1240.57319) (13101.43292
1238.68778)))
("SF_PLANTING" 1 ((13101.43292 3501.13122) (13103.31821 3503.01663) (13105.20362 3501.13122) (13103.31821 3499.24581)))
("SF_SOLAR" 1 ((13112.74514 8176.84762) (13114.63043 8178.73303) (13116.51584 8176.84762) (13114.63043 8174.96233)))
("SF_SOLAR" 1 ((13112.74514 8027.90351) (13114.63043 8029.78880) (13116.51584 8027.90351) (13114.63043 8026.01810)))
("SF_SOLAR" 1 ((13118.40124 8018.47658) (13120.28654 8020.36199) (13122.17195 8018.47658) (13120.28654 8016.59129)))
("SF_PLANTING" 1 ((13119.60486 6552.33993) (13119.60486 6538.46833) (13129.55826 6532.27896) (13133.32952 6538.46833)
(13132.27998 6549.61889)))
("SF_MASONRY_AND_ARCH" 1 ((13120.28654 2926.09355) (13122.17195 2927.97885) (13124.05735 2926.09355) (13122.17195
2924.20814)))
("SF_SOLAR" 1 ((13122.17195 8044.87183) (13124.05735 8046.75713) (13125.94265 8044.87183) (13124.05735 8042.98643)))
("SF_SOLAR" 1 ((13131.59876 8035.44491) (13133.48416 8037.33032) (13135.36957 8035.44491) (13133.48416 8033.55962)))
("SF_SOLAR" 1 ((13133.48416 8061.84016) (13135.36957 8063.72545) (13137.25486 8061.84016) (13135.36957 8059.95475)))
("SF_PLANTING" 1 ((13135.36957 635.36957) (13137.25486 637.25486) (13139.14027 635.36957) (13137.25486 633.48416)))
("SF_MASONRY_AND_ARCH" 1 ((13137.25486 2273.75566) (13139.14027 2275.64106) (13141.02568 2273.75566) (13139.14027
2271.87025)))
("SF_SOLAR" 1 ((13139.14027 8054.29864) (13141.02568 8056.18405) (13142.91097 8054.29864) (13141.02568 8052.41324)))
("SF_SOLAR" 1 ((13142.91097 8080.69378) (13144.79638 8082.57919) (13146.68179 8080.69378) (13144.79638 8078.80848)))
("SF_SOLAR" 1 ((13152.33790 8095.77681) (13154.22319 8097.66210) (13156.10860 8095.77681) (13154.22319 8093.89140)))
("SF_SOLAR" 1 ((13152.33790 8073.15238) (13154.22319 8075.03767) (13156.10860 8073.15238) (13154.22319 8071.26697)))
("SF_SOLAR" 1 ((13157.99400 7950.60328) (13159.87930 7952.48869) (13161.76471 7950.60328) (13159.87930 7948.71799)))
("SF_SOLAR" 1 ((13157.99400 7924.20814) (13159.87930 7926.09355) (13161.76471 7924.20814) (13159.87930 7922.32274)))
("SF_SOLAR" 1 ((13163.65011 8092.00600) (13165.53541 8093.89140) (13167.42081 8092.00600) (13165.53541 8090.12070)))
("SF_SOLAR" 1 ((13165.53541 8195.70136) (13167.42081 8197.58676) (13169.30622 8195.70136) (13167.42081 8193.81595)))
("SF_SOLAR" 1 ((13165.53541 8118.40124) (13167.42081 8120.28654) (13169.30622 8118.40124) (13167.42081 8116.51584)))
("SF_SOLAR" 1 ((13174.96233 8108.97432) (13176.84762 8110.85973) (13178.73303 8108.97432) (13176.84762 8107.08903)))
("SF_SOLAR" 1 ((13176.84762 8137.25486) (13178.73303 8139.14027) (13180.61844 8137.25486) (13178.73303 8135.36957)))
("SF_PLANTING" 1 ((13180.61844 3342.76018) (13182.50373 3344.64559) (13184.38914 3342.76018) (13182.50373 3340.87477)))
("SF_MASONRY_AND_ARCH" 1 ((13184.38914 1214.17794) (13186.27455 1216.06335) (13188.15984 1214.17794) (13186.27455
1212.29265)))
("SF_SOLAR" 1 ((13186.27455 8129.71346) (13188.15984 8131.59876) (13190.04525 8129.71346) (13188.15984 8127.82805)))
("SF_SOLAR" 1 ((13188.15984 8156.10860) (13190.04525 8157.99400) (13191.93066 8156.10860) (13190.04525 8154.22319)))
("SF_SOLAR" 1 ((13199.47206 8171.19152) (13201.35747 8173.07692) (13203.24287 8171.19152) (13201.35747 8169.30622)))
("SF_SOLAR" 1 ((13199.47206 8148.56708) (13201.35747 8150.45249) (13203.24287 8148.56708) (13201.35747 8146.68179)))
("SF_SOLAR" 1 ((13201.35747 8225.86731) (13203.24287 8227.75260) (13205.12817 8225.86731) (13203.24287 8223.98190)))
("SF_SOLAR" 1 ((13203.24287 8110.85973) (13205.12817 8112.74514) (13207.01357 8110.85973) (13205.12817 8108.97432)))
("SF_SOLAR" 1 ((13203.24287 7982.65464) (13205.12817 7984.53993) (13207.01357 7982.65464) (13205.12817 7980.76923)))
("SF_SOLAR" 1 ((13210.78428 8163.65011) (13212.66968 8165.53541) (13214.55509 8163.65011) (13212.66968 8161.76471)))
("SF_PLANTING" 1 ((13214.55509 3897.05882) (13216.44038 3898.94423) (13218.32579 3897.05882) (13216.44038 3895.17342)))
("SF_SOLAR" 1 ((13225.86731 8071.26697) (13227.75260 8073.15238) (13229.63801 8071.26697) (13227.75260 8069.38156)))
("SF_SOLAR" 1 ((13225.86731 7948.71799) (13227.75260 7950.60328) (13229.63801 7948.71799) (13227.75260 7946.83258)))
("SF_SOLAR" 1 ((13244.72093 7869.53247) (13246.60633 7871.41776) (13248.49174 7869.53247) (13246.60633 7867.64706)))
("SF_SOLAR" 1 ((13248.49174 7984.53993) (13250.37704 7986.42534) (13252.26244 7984.53993) (13250.37704 7982.65464)))
("SF_SOLAR" 1 ((13261.68925 7863.87636) (13263.57466 7865.76165) (13265.46007 7863.87636) (13263.57466 7861.99095)))
("SF_SOLAR" 1 ((13282.42839 7850.67873) (13284.31369 7852.56414) (13286.19910 7850.67873) (13284.31369 7848.79333)))
("SF_SOLAR" 1 ((13293.74061 8152.33790) (13295.62590 8154.22319) (13297.51131 8152.33790) (13295.62590 8150.45249)))
("SF_SOLAR" 1 ((13299.39672 7869.53247) (13301.28201 7871.41776) (13303.16742 7869.53247) (13301.28201 7867.64706)))
("SF_MASONRY_AND_ARCH" 1 ((13310.70894 2004.14785) (13312.59423 2006.03314) (13314.47964 2004.14785) (13312.59423
2002.26244)))
("SF_SOLAR" 1 ((13316.36505 8174.96233) (13318.25034 8176.84762) (13320.13575 8174.96233) (13318.25034 8173.07692)))
("SF_SOLAR" 1 ((13316.36505 8071.26697) (13318.25034 8073.15238) (13320.13575 8071.26697) (13318.25034 8069.38156)))
("SF_MASONRY_AND_ARCH" 1 ((13316.36505 1493.21267) (13318.25034 1495.09808) (13320.13575 1493.21267) (13318.25034
1491.32726)))
("SF_SOLAR" 1 ((13331.44796 7886.50079) (13333.33337 7888.38609) (13335.21867 7886.50079) (13333.33337 7884.61538)))
("SF_SOLAR" 1 ((13335.21867 7941.17647) (13337.10407 7943.06188) (13338.98948 7941.17647) (13337.10407 7939.29106)))
("SF_SOLAR" 1 ((13342.76018 7990.19604) (13344.64559 7992.08145) (13346.53088 7990.19604) (13344.64559 7988.31075)))
("SF_SOLAR" 1 ((13354.07240 7967.57161) (13355.95781 7969.45701) (13357.84310 7967.57161) (13355.95781 7965.68631)))
("SF_PLANTING" 1 ((13363.49921 4012.06640) (13365.38462 4013.95170) (13367.27002 4012.06640) (13365.38462 4010.18100)))
("SF_SOLAR" 1 ((13384.23835 8118.40124) (13386.12364 8120.28654) (13388.00905 8118.40124) (13386.12364 8116.51584)))
("SF_SOLAR" 1 ((13384.23835 8082.57919) (13386.12364 8084.46459) (13388.00905 8082.57919) (13386.12364 8080.69378)))
("SF_SOLAR" 1 ((13389.89446 8012.82048) (13391.77975 8014.70588) (13393.66516 8012.82048) (13391.77975 8010.93518)))
("SF_SOLAR" 1 ((13418.17500 8009.04977) (13420.06029 8010.93518) (13421.94570 8009.04977) (13420.06029 8007.16437)))
("SF_SOLAR" 1 ((13433.25792 7995.85215) (13435.14333 7997.73756) (13437.02862 7995.85215) (13435.14333 7993.96686)))
("SF_SOLAR" 1 ((13448.34084 7995.85215) (13450.22624 7997.73756) (13452.11165 7995.85215) (13450.22624 7993.96686)))
("SF_SOLAR" 1 ((13467.19457 8039.21572) (13469.07998 8041.10102) (13470.96527 8039.21572) (13469.07998 8037.33032)))
("SF_SOLAR" 1 ((13474.73609 8182.50373) (13476.62138 8184.38914) (13478.50679 8182.50373) (13476.62138 8180.61844)))
("SF_SOLAR" 1 ((13486.04830 8195.70136) (13487.93360 8197.58676) (13489.81900 8195.70136) (13487.93360 8193.81595)))
("SF_SOLAR" 1 ((13508.67274 7984.53993) (13510.55803 7986.42534) (13512.44344 7984.53993) (13510.55803 7982.65464)))
("SF_SOLAR" 1 ((13518.09955 8007.16437) (13519.98495 8009.04977) (13521.87025 8007.16437) (13519.98495 8005.27907)))
("SF_SOLAR" 1 ((13527.52636 7854.44943) (13529.41176 7856.33484) (13531.29717 7854.44943) (13529.41176 7852.56414)))
("SF_SOLAR" 1 ((13535.06787 8152.33790) (13536.95328 8154.22319) (13538.83857 8152.33790) (13536.95328 8150.45249)))
("SF_SOLAR" 1 ((13582.20215 7869.53247) (13584.08744 7871.41776) (13585.97285 7869.53247) (13584.08744 7867.64706)))
("SF_SOLAR" 1 ((13602.94118 7882.72998) (13604.82658 7884.61538) (13606.71188 7882.72998) (13604.82658 7880.84468)))
("SF_SOLAR" 1 ((13602.94118 7871.41776) (13604.82658 7873.30317) (13606.71188 7871.41776) (13604.82658 7869.53247)))
("SF_PLANTING" 1 ((13606.71188 3695.32432) (13608.59729 3697.20962) (13610.48269 3695.32432) (13608.59729 3693.43891)))
("SF_SOLAR" 1 ((13640.64853 7871.41776) (13642.53394 7873.30317) (13644.41934 7871.41776) (13642.53394 7869.53247)))
("SF_SOLAR" 1 ((13693.43891 7984.53993) (13695.32432 7986.42534) (13697.20962 7984.53993) (13695.32432 7982.65464)))
("SF_SOLAR" 1 ((13700.98043 7990.19604) (13702.86572 7992.08145) (13704.75113 7990.19604) (13702.86572 7988.31075)))
("SF_SOLAR" 1 ((13704.75113 7854.44943) (13706.63654 7856.33484) (13708.52183 7854.44943) (13706.63654 7852.56414)))
("SF_SOLAR" 1 ((13716.06335 8022.24740) (13717.94876 8024.13269) (13719.83405 8022.24740) (13717.94876 8020.36199)))
("SF_SOLAR" 1 ((13723.60486 8029.78880) (13725.49016 8031.67421) (13727.37557 8029.78880) (13725.49016 8027.90351)))
("SF_SOLAR" 1 ((13729.26097 7984.53993) (13731.14627 7986.42534) (13733.03167 7984.53993) (13731.14627 7982.65464)))
("SF_SOLAR" 1 ((13742.45848 8195.70136) (13744.34389 8197.58676) (13746.22930 8195.70136) (13744.34389 8193.81595)))
("SF_SOLAR" 1 ((13742.45848 8180.61844) (13744.34389 8182.50373) (13746.22930 8180.61844) (13744.34389 8178.73303)))
("SF_SOLAR" 1 ((13768.85373 8174.96233) (13770.73903 8176.84762) (13772.62443 8174.96233) (13770.73903 8173.07692)))
("SF_SOLAR" 1 ((13780.16595 8069.38156) (13782.05124 8071.26697) (13783.93665 8069.38156) (13782.05124 8067.49627)))
("SF_SOLAR" 1 ((13795.24887 8152.33790) (13797.13428 8154.22319) (13799.01957 8152.33790) (13797.13428 8150.45249)))
("SF_SOLAR" 1 ((13802.79038 7926.09355) (13804.67568 7927.97885) (13806.56109 7926.09355) (13804.67568 7924.20814)))
("SF_SOLAR" 1 ((13802.79038 7890.27149) (13804.67568 7892.15690) (13806.56109 7890.27149) (13804.67568 7888.38609)))
("SF_SOLAR" 1 ((13810.33179 8176.84762) (13812.21719 8178.73303) (13814.10260 8176.84762) (13812.21719 8174.96233)))
("SF_SOLAR" 1 ((13817.87330 8195.70136) (13819.75871 8197.58676) (13821.64400 8195.70136) (13819.75871 8193.81595)))
("SF_SOLAR" 1 ((13827.30011 7869.53247) (13829.18552 7871.41776) (13831.07093 7869.53247) (13829.18552 7867.64706)))
("SF_SOLAR" 1 ((13866.89287 7993.96686) (13868.77828 7995.85215) (13870.66369 7993.96686) (13868.77828 7992.08145)))
("SF_SOLAR" 1 ((13874.43439 7850.67873) (13876.31980 7852.56414) (13878.20509 7850.67873) (13876.31980 7848.79333)))
("SF_SOLAR" 1 ((13878.20509 7929.86425) (13880.09050 7931.74966) (13881.97590 7929.86425) (13880.09050 7927.97885)))
("SF_SOLAR" 1 ((13887.63201 7944.94717) (13889.51731 7946.83258) (13891.40271 7944.94717) (13889.51731 7943.06188)))
("SF_SOLAR" 1 ((13889.51731 8033.55962) (13891.40271 8035.44491) (13893.28812 8033.55962) (13891.40271 8031.67421)))
("SF_SOLAR" 1 ((13893.28812 8071.26697) (13895.17342 8073.15238) (13897.05882 8071.26697) (13895.17342 8069.38156)))
("SF_SOLAR" 1 ((13897.05882 7931.74966) (13898.94423 7933.63495) (13900.82952 7931.74966) (13898.94423 7929.86425)))
("SF_SOLAR" 1 ((13898.94423 7961.91550) (13900.82952 7963.80090) (13902.71493 7961.91550) (13900.82952 7960.03020)))
("SF_SOLAR" 1 ((13904.60034 7948.71799) (13906.48563 7950.60328) (13908.37104 7948.71799) (13906.48563 7946.83258)))
("SF_SOLAR" 1 ((13910.25645 7980.76923) (13912.14174 7982.65464) (13914.02715 7980.76923) (13912.14174 7978.88382)))
("SF_SOLAR" 1 ((13915.91256 7886.50079) (13917.79785 7888.38609) (13919.68326 7886.50079) (13917.79785 7884.61538)))
("SF_SOLAR" 1 ((13917.79785 7965.68631) (13919.68326 7967.57161) (13921.56867 7965.68631) (13919.68326 7963.80090)))
("SF_PLANTING" 1 ((13917.79785 524.13269) (13919.68326 526.01810) (13921.56867 524.13269) (13919.68326 522.24740)))
("SF_SOLAR" 1 ((13919.68326 7997.73756) (13921.56867 7999.62296) (13923.45396 7997.73756) (13921.56867 7995.85215)))
("SF_SOLAR" 1 ((13923.45396 8046.75713) (13925.33937 8048.64253) (13927.22477 8046.75713) (13925.33937 8044.87183)))
("SF_SOLAR" 1 ((13927.22477 7982.65464) (13929.11007 7984.53993) (13930.99548 7982.65464) (13929.11007 7980.76923)))
("SF_PLANTING" 1 ((13927.22477 371.41776) (13929.11007 373.30317) (13930.99548 371.41776) (13929.11007 369.53247)))
("SF_SOLAR" 1 ((13930.99548 8016.59129) (13932.88088 8018.47658) (13934.76618 8016.59129) (13932.88088 8014.70588)))
("SF_SOLAR" 1 ((13942.30769 7999.62296) (13944.19310 8001.50826) (13946.07839 7999.62296) (13944.19310 7997.73756)))
("SF_SOLAR" 1 ((13944.19310 8031.67421) (13946.07839 8033.55962) (13947.96380 8031.67421) (13946.07839 8029.78880)))
("SF_SOLAR" 1 ((13946.07839 7952.48869) (13947.96380 7954.37410) (13949.84921 7952.48869) (13947.96380 7950.60328)))
("SF_SOLAR" 1 ((13953.61991 8092.00600) (13955.50532 8093.89140) (13957.39061 8092.00600) (13955.50532 8090.12070)))
("SF_SOLAR" 1 ((13953.61991 8016.59129) (13955.50532 8018.47658) (13957.39061 8016.59129) (13955.50532 8014.70588)))
("SF_SOLAR" 1 ((13955.50532 8052.41324) (13957.39061 8054.29864) (13959.27602 8052.41324) (13957.39061 8050.52794)))
("SF_SOLAR" 1 ((13964.93213 8035.44491) (13966.81753 8037.33032) (13968.70283 8035.44491) (13966.81753 8033.55962)))
("SF_SOLAR" 1 ((13966.81753 8069.38156) (13968.70283 8071.26697) (13970.58824 8069.38156) (13968.70283 8067.49627)))
("SF_SOLAR" 1 ((13976.24434 8052.41324) (13978.12975 8054.29864) (13980.01505 8052.41324) (13978.12975 8050.52794)))
("SF_SOLAR" 1 ((13978.12975 8086.34989) (13980.01505 8088.23529) (13981.90045 8086.34989) (13980.01505 8084.46459)))
("SF_SOLAR" 1 ((13983.78586 8174.96233) (13985.67115 8176.84762) (13987.55656 8174.96233) (13985.67115 8173.07692)))
("SF_SOLAR" 1 ((13987.55656 8067.49627) (13989.44197 8069.38156) (13991.32726 8067.49627) (13989.44197 8065.61086)))
("SF_SOLAR" 1 ((13987.55656 7982.65464) (13989.44197 7984.53993) (13991.32726 7982.65464) (13989.44197 7980.76923)))
("SF_SOLAR" 1 ((13989.44197 8105.20362) (13991.32726 8107.08903) (13993.21267 8105.20362) (13991.32726 8103.31821)))
("SF_SOLAR" 1 ((13991.32726 8195.70136) (13993.21267 8197.58676) (13995.09808 8195.70136) (13993.21267 8193.81595)))
("SF_SOLAR" 1 ((13995.09808 8088.23529) (13996.98337 8090.12070) (13998.86878 8088.23529) (13996.98337 8086.34989)))
("SF_SOLAR" 1 ((14000.75419 8124.05735) (14002.63948 8125.94265) (14004.52489 8124.05735) (14002.63948 8122.17195)))
("SF_SOLAR" 1 ((14006.41029 7924.20814) (14008.29559 7926.09355) (14010.18100 7924.20814) (14008.29559 7922.32274)))
("SF_SOLAR" 1 ((14008.29559 8108.97432) (14010.18100 8110.85973) (14012.06640 8108.97432) (14010.18100 8107.08903)))
("SF_SOLAR" 1 ((14008.29559 8020.36199) (14010.18100 8022.24740) (14012.06640 8020.36199) (14010.18100 8018.47658)))
("SF_SOLAR" 1 ((14012.06640 8141.02568) (14013.95170 8142.91097) (14015.83710 8141.02568) (14013.95170 8139.14027)))
("SF_SOLAR" 1 ((14019.60781 8229.63801) (14021.49321 8231.52342) (14023.37862 8229.63801) (14021.49321 8227.75260)))
("SF_SOLAR" 1 ((14021.49321 8029.78880) (14023.37862 8031.67421) (14025.26391 8029.78880) (14023.37862 8027.90351)))
("SF_SOLAR" 1 ((14029.03473 8137.25486) (14030.92002 8139.14027) (14032.80543 8137.25486) (14030.92002 8135.36957)))
("SF_SOLAR" 1 ((14044.11765 8110.85973) (14046.00305 8112.74514) (14047.88835 8110.85973) (14046.00305 8108.97432)))
("SF_SOLAR" 1 ((14044.11765 8071.26697) (14046.00305 8073.15238) (14047.88835 8071.26697) (14046.00305 8069.38156)))
("SF_SOLAR" 1 ((14051.65916 7984.53993) (14053.54446 7986.42534) (14055.42986 7984.53993) (14053.54446 7982.65464)))
("SF_SOLAR" 1 ((14066.74208 8201.35747) (14068.62749 8203.24287) (14070.51278 8201.35747) (14068.62749 8199.47206)))
("SF_SOLAR" 1 ((14074.28360 8071.26697) (14076.16889 8073.15238) (14078.05430 8071.26697) (14076.16889 8069.38156)))
("SF_SOLAR" 1 ((14079.93971 8216.44038) (14081.82500 8218.32579) (14083.71041 8216.44038) (14081.82500 8214.55509)))
("SF_SOLAR" 1 ((14085.59581 8152.33790) (14087.48111 8154.22319) (14089.36652 8152.33790) (14087.48111 8150.45249)))
("SF_SOLAR" 1 ((14096.90803 7926.09355) (14098.79333 7927.97885) (14100.67873 7926.09355) (14098.79333 7924.20814)))
("SF_SOLAR" 1 ((14100.67873 8176.84762) (14102.56414 8178.73303) (14104.44943 8176.84762) (14102.56414 8174.96233)))
("SF_PLANTING" 1 ((14102.56369 1025.94989) (14084.76674 1037.10124) (14080.09389 1052.03620) (14087.63631 1070.89084)
(14098.79378 1080.99751) (14106.33484 1082.04072) (14113.72805 1078.27715) (14120.36188 1067.11821) (14121.26357
1044.49378) (14113.86900 1033.18914)))
("SF_SOLAR" 1 ((14104.44943 7886.50079) (14106.33484 7888.38609) (14108.22025 7886.50079) (14106.33484 7884.61538)))
("SF_SOLAR" 1 ((14111.99095 8195.70136) (14113.87636 8197.58676) (14115.76165 8195.70136) (14113.87636 8193.81595)))
("SF_SOLAR" 1 ((14119.53247 8152.33790) (14121.41776 8154.22319) (14123.30317 8152.33790) (14121.41776 8150.45249)))
("SF_SOLAR" 1 ((14119.53247 7984.53993) (14121.41776 7986.42534) (14123.30317 7984.53993) (14121.41776 7982.65464)))
("SF_SOLAR" 1 ((14119.53247 7952.48869) (14121.41776 7954.37410) (14123.30317 7952.48869) (14121.41776 7950.60328)))
("SF_SOLAR" 1 ((14142.15690 8152.33790) (14144.04219 8154.22319) (14145.92760 8152.33790) (14144.04219 8150.45249)))
("SF_SOLAR" 1 ((14161.01052 7960.03020) (14162.89593 7961.91550) (14164.78133 7960.03020) (14162.89593 7958.14480)))
("SF_SOLAR" 1 ((14164.78133 8124.05735) (14166.66663 8125.94265) (14168.55204 8124.05735) (14166.66663 8122.17195)))
("SF_SOLAR" 1 ((14166.66663 7984.53993) (14168.55204 7986.42534) (14170.43744 7984.53993) (14168.55204 7982.65464)))
("SF_SOLAR" 1 ((14168.55204 7865.76165) (14170.43744 7867.64706) (14172.32274 7865.76165) (14170.43744 7863.87636)))
("SF_SOLAR" 1 ((14187.40577 8020.36199) (14189.29106 8022.24740) (14191.17647 8020.36199) (14189.29106 8018.47658)))
("SF_SOLAR" 1 ((14187.40577 7993.96686) (14189.29106 7995.85215) (14191.17647 7993.96686) (14189.29106 7992.08145)))
("SF_SOLAR" 1 ((14193.06188 7937.40577) (14194.94717 7939.29106) (14196.83258 7937.40577) (14194.94717 7935.52036)))
("SF_PLANTING" 1 ((14200.60328 265.83710) (14202.48869 267.72251) (14204.37410 265.83710) (14202.48869 263.95170)))
("SF_SOLAR" 1 ((14202.48869 7941.17647) (14204.37410 7943.06188) (14206.25939 7941.17647) (14204.37410 7939.29106)))
("SF_SOLAR" 1 ((14213.80090 7969.45701) (14215.68631 7971.34242) (14217.57161 7969.45701) (14215.68631 7967.57161)))
("SF_SOLAR" 1 ((14225.11312 7980.76923) (14226.99853 7982.65464) (14228.88382 7980.76923) (14226.99853 7978.88382)))
("SF_SOLAR" 1 ((14232.65464 8118.40124) (14234.53993 8120.28654) (14236.42534 8118.40124) (14234.53993 8116.51584)))
("SF_SOLAR" 1 ((14249.62296 8010.93518) (14251.50826 8012.82048) (14253.39367 8010.93518) (14251.50826 8009.04977)))
("SF_SOLAR" 1 ((14277.90351 8131.59876) (14279.78880 8133.48416) (14281.67421 8131.59876) (14279.78880 8129.71346)))
("SF_PLANTING" 1 ((14279.78880 3819.75871) (14281.67421 3821.64400) (14283.55962 3819.75871) (14281.67421 3817.87330)))
("SF_SOLAR" 1 ((14281.67421 7982.65464) (14283.55962 7984.53993) (14285.44491 7982.65464) (14283.55962 7980.76923)))
("SF_SOLAR" 1 ((14296.75713 7988.31075) (14298.64253 7990.19604) (14300.52794 7988.31075) (14298.64253 7986.42534)))
("SF_SOLAR" 1 ((14300.52794 8022.24740) (14302.41324 8024.13269) (14304.29864 8022.24740) (14302.41324 8020.36199)))
("SF_SOLAR" 1 ((14340.12070 8142.91097) (14342.00600 8144.79638) (14343.89140 8142.91097) (14342.00600 8141.02568)))
("SF_SOLAR" 1 ((14345.77681 7924.20814) (14347.66210 7926.09355) (14349.54751 7924.20814) (14347.66210 7922.32274)))
("SF_SOLAR" 1 ((14357.08903 8180.61844) (14358.97432 8182.50373) (14360.85973 8180.61844) (14358.97432 8178.73303)))
("SF_SOLAR" 1 ((14368.40124 7924.20814) (14370.28654 7926.09355) (14372.17195 7924.20814) (14370.28654 7922.32274)))
("SF_SOLAR" 1 ((14372.17195 7865.76165) (14374.05735 7867.64706) (14375.94265 7865.76165) (14374.05735 7863.87636)))
("SF_SOLAR" 1 ((14375.94265 7960.03020) (14377.82805 7961.91550) (14379.71346 7960.03020) (14377.82805 7958.14480)))
("SF_SOLAR" 1 ((14387.25486 7865.76165) (14389.14027 7867.64706) (14391.02568 7865.76165) (14389.14027 7863.87636)))
("SF_SOLAR" 1 ((14391.02568 8174.96233) (14392.91097 8176.84762) (14394.79638 8174.96233) (14392.91097 8173.07692)))
("SF_SOLAR" 1 ((14391.02568 8131.59876) (14392.91097 8133.48416) (14394.79638 8131.59876) (14392.91097 8129.71346)))
("SF_SOLAR" 1 ((14406.10860 8035.44491) (14407.99400 8037.33032) (14409.87930 8035.44491) (14407.99400 8033.55962)))
("SF_SOLAR" 1 ((14413.65011 7886.50079) (14415.53541 7888.38609) (14417.42081 7886.50079) (14415.53541 7884.61538)))
("SF_PLANTING" 1 ((14415.53541 3423.83111) (14417.42081 3425.71640) (14419.30622 3423.83111) (14417.42081 3421.94570)))
("SF_SOLAR" 1 ((14436.27455 7861.99095) (14438.15984 7863.87636) (14440.04525 7861.99095) (14438.15984 7860.10554)))
("SF_SOLAR" 1 ((14449.47206 7995.85215) (14451.35747 7997.73756) (14453.24287 7995.85215) (14451.35747 7993.96686)))
("SF_SOLAR" 1 ((14455.12817 7888.38609) (14457.01357 7890.27149) (14458.89898 7888.38609) (14457.01357 7886.50079)))
("SF_SOLAR" 1 ((14458.89898 8176.84762) (14460.78428 8178.73303) (14462.66968 8176.84762) (14460.78428 8174.96233)))
("SF_SOLAR" 1 ((14458.89898 7865.76165) (14460.78428 7867.64706) (14462.66968 7865.76165) (14460.78428 7863.87636)))
("SF_SOLAR" 1 ((14466.44038 8195.70136) (14468.32579 8197.58676) (14470.21120 8195.70136) (14468.32579 8193.81595)))
("SF_SOLAR" 1 ((14477.75260 8125.94265) (14479.63801 8127.82805) (14481.52342 8125.94265) (14479.63801 8124.05735)))
("SF_PLANTING" 1 ((14490.95023 3489.81900) (14492.83563 3491.70441) (14494.72093 3489.81900) (14492.83563 3487.93360)))
("SF_SOLAR" 1 ((14515.46007 8152.33790) (14517.34536 8154.22319) (14519.23077 8152.33790) (14517.34536 8150.45249)))
("SF_SOLAR" 1 ((14526.77229 8075.03767) (14528.65758 8076.92308) (14530.54299 8075.03767) (14528.65758 8073.15238)))
("SF_SOLAR" 1 ((14526.77229 8050.52794) (14528.65758 8052.41324) (14530.54299 8050.52794) (14528.65758 8048.64253)))
("SF_SOLAR" 1 ((14526.77229 8031.67421) (14528.65758 8033.55962) (14530.54299 8031.67421) (14528.65758 8029.78880)))
("SF_SOLAR" 1 ((14547.51131 8082.57919) (14549.39672 8084.46459) (14551.28201 8082.57919) (14549.39672 8080.69378)))
("SF_SOLAR" 1 ((14572.02115 8120.28654) (14573.90645 8122.17195) (14575.79186 8120.28654) (14573.90645 8118.40124)))
("SF_SOLAR" 1 ((14583.33337 7860.10554) (14585.21867 7861.99095) (14587.10407 7860.10554) (14585.21867 7858.22025)))
("SF_SOLAR" 1 ((14600.30170 8016.59129) (14602.18699 8018.47658) (14604.07240 8016.59129) (14602.18699 8014.70588)))
("SF_SOLAR" 1 ((14602.18699 8118.40124) (14604.07240 8120.28654) (14605.95781 8118.40124) (14604.07240 8116.51584)))
("SF_SOLAR" 1 ((14609.72851 8044.87183) (14611.61391 8046.75713) (14613.49921 8044.87183) (14611.61391 8042.98643)))
("SF_SOLAR" 1 ((14613.49921 8127.82805) (14615.38462 8129.71346) (14617.27002 8127.82805) (14615.38462 8125.94265)))
("SF_SOLAR" 1 ((14639.89446 8174.96233) (14641.77975 8176.84762) (14643.66516 8174.96233) (14641.77975 8173.07692)))
("SF_SOLAR" 1 ((14681.37251 8195.70136) (14683.25792 8197.58676) (14685.14333 8195.70136) (14683.25792 8193.81595)))
("SF_SOLAR" 1 ((14685.14333 7984.53993) (14687.02862 7986.42534) (14688.91403 7984.53993) (14687.02862 7982.65464)))
("SF_SOLAR" 1 ((14703.99695 8084.46459) (14705.88235 8086.34989) (14707.76776 8084.46459) (14705.88235 8082.57919)))
("SF_SOLAR" 1 ((14707.76776 7888.38609) (14709.65305 7890.27149) (14711.53846 7888.38609) (14709.65305 7886.50079)))
("SF_SOLAR" 1 ((14726.62138 7856.33484) (14728.50679 7858.22025) (14730.39219 7856.33484) (14728.50679 7854.44943)))
("SF_SOLAR" 1 ((14737.93360 7882.72998) (14739.81900 7884.61538) (14741.70441 7882.72998) (14739.81900 7880.84468)))
("SF_SOLAR" 1 ((14749.24581 8080.69378) (14751.13122 8082.57919) (14753.01663 8080.69378) (14751.13122 8078.80848)))
("SF_SOLAR" 1 ((14753.01663 8050.52794) (14754.90192 8052.41324) (14756.78733 8050.52794) (14754.90192 8048.64253)))
("SF_SOLAR" 1 ((14775.64106 8127.82805) (14777.52636 8129.71346) (14779.41176 8127.82805) (14777.52636 8125.94265)))
("SF_SOLAR" 1 ((14798.26550 8131.59876) (14800.15079 8133.48416) (14802.03620 8131.59876) (14800.15079 8129.71346)))
("SF_SOLAR" 1 ((14802.03620 8024.13269) (14803.92161 8026.01810) (14805.80690 8024.13269) (14803.92161 8022.24740)))
("SF_SOLAR" 1 ((14803.92161 7843.13722) (14805.80690 7845.02262) (14807.69231 7843.13722) (14805.80690 7841.25192)))
("SF_SOLAR" 1 ((14819.00452 7926.09355) (14820.88993 7927.97885) (14822.77523 7926.09355) (14820.88993 7924.20814)))
("SF_SOLAR" 1 ((14822.77523 8124.05735) (14824.66063 8125.94265) (14826.54604 8124.05735) (14824.66063 8122.17195)))
("SF_SOLAR" 1 ((14830.31674 7946.83258) (14832.20215 7948.71799) (14834.08744 7946.83258) (14832.20215 7944.94717)))
("SF_SOLAR" 1 ((14834.08744 8131.59876) (14835.97285 8133.48416) (14837.85826 8131.59876) (14835.97285 8129.71346)))
("SF_SOLAR" 1 ((14837.85826 7937.40577) (14839.74355 7939.29106) (14841.62896 7937.40577) (14839.74355 7935.52036)))
("SF_SOLAR" 1 ((14839.74355 8012.82048) (14841.62896 8014.70588) (14843.51437 8012.82048) (14841.62896 8010.93518)))
("SF_SOLAR" 1 ((14843.51437 8124.05735) (14845.39966 8125.94265) (14847.28507 8124.05735) (14845.39966 8122.17195)))
("SF_SOLAR" 1 ((14847.28507 8039.21572) (14849.17048 8041.10102) (14851.05577 8039.21572) (14849.17048 8037.33032)))
("SF_SOLAR" 1 ((14862.36799 8082.57919) (14864.25339 8084.46459) (14866.13880 8082.57919) (14864.25339 8080.69378)))
("SF_SOLAR" 1 ((14862.36799 7975.11312) (14864.25339 7976.99853) (14866.13880 7975.11312) (14864.25339 7973.22771)))
("SF_SOLAR" 1 ((14864.25339 8003.39367) (14866.13880 8005.27907) (14868.02410 8003.39367) (14866.13880 8001.50826)))
("SF_SOLAR" 1 ((14873.68020 7993.96686) (14875.56561 7995.85215) (14877.45102 7993.96686) (14875.56561 7992.08145)))
("SF_SOLAR" 1 ((14877.45102 8024.13269) (14879.33631 8026.01810) (14881.22172 8024.13269) (14879.33631 8022.24740)))
("SF_SOLAR" 1 ((14884.99242 8016.59129) (14886.87783 8018.47658) (14888.76324 8016.59129) (14886.87783 8014.70588)))
("SF_PLANTING" 1 ((14886.87783 3695.32432) (14888.76324 3697.20962) (14890.64853 3695.32432) (14888.76324 3693.43891)))
("SF_SOLAR" 1 ((14892.53394 8027.90351) (14894.41934 8029.78880) (14896.30464 8027.90351) (14894.41934 8026.01810)))
("SF_SOLAR" 1 ((14894.41934 7950.60328) (14896.30464 7952.48869) (14898.19005 7950.60328) (14896.30464 7948.71799)))
("SF_SOLAR" 1 ((14896.30464 8095.77681) (14898.19005 8097.66210) (14900.07545 8095.77681) (14898.19005 8093.89140)))
("SF_MASONRY_AND_ARCH" 1 ((14905.73156 2611.23676) (14907.61686 2613.12217) (14909.50226 2611.23676) (14907.61686
2609.35147)))
("SF_SOLAR" 1 ((14922.69989 7993.96686) (14924.58518 7995.85215) (14926.47059 7993.96686) (14924.58518 7992.08145)))
("SF_SOLAR" 1 ((14934.01210 8116.51584) (14935.89740 8118.40124) (14937.78281 8116.51584) (14935.89740 8114.63043)))
("SF_SOLAR" 1 ((14941.55351 8197.58676) (14943.43891 8199.47206) (14945.32432 8197.58676) (14943.43891 8195.70136)))
("SF_SOLAR" 1 ((14941.55351 8108.97432) (14943.43891 8110.85973) (14945.32432 8108.97432) (14943.43891 8107.08903)))
("SF_SOLAR" 1 ((14945.32432 8141.02568) (14947.20962 8142.91097) (14949.09502 8141.02568) (14947.20962 8139.14027)))
("SF_SOLAR" 1 ((14960.40724 8156.10860) (14962.29265 8157.99400) (14964.17794 8156.10860) (14962.29265 8154.22319)))
("SF_SOLAR" 1 ((14964.17794 8146.68179) (14966.06335 8148.56708) (14967.94876 8146.68179) (14966.06335 8144.79638)))
("SF_SOLAR" 1 ((14966.06335 8225.86731) (14967.94876 8227.75260) (14969.83405 8225.86731) (14967.94876 8223.98190)))
("SF_SOLAR" 1 ((14979.26097 8082.57919) (14981.14627 8084.46459) (14983.03167 8082.57919) (14981.14627 8080.69378)))
("SF_SOLAR" 1 ((15005.65611 8075.03767) (15007.54152 8076.92308) (15009.42681 8075.03767) (15007.54152 8073.15238)))
("SF_SOLAR" 1 ((15028.28054 8195.70136) (15030.16595 8197.58676) (15032.05124 8195.70136) (15030.16595 8193.81595)))
("SF_SOLAR" 1 ((15032.05124 7867.64706) (15033.93665 7869.53247) (15035.82206 7867.64706) (15033.93665 7865.76165)))
("SF_SOLAR" 1 ((15039.59276 7948.71799) (15041.47817 7950.60328) (15043.36346 7948.71799) (15041.47817 7946.83258)))
("SF_SOLAR" 1 ((15043.36346 7886.50079) (15045.24887 7888.38609) (15047.13428 7886.50079) (15045.24887 7884.61538)))
("SF_PLANTING" 1 ((15073.52941 3676.47059) (15075.41482 3678.35600) (15077.30011 3676.47059) (15075.41482 3674.58518)))
("SF_SOLAR" 1 ((15081.07093 7911.01052) (15082.95622 7912.89593) (15084.84163 7911.01052) (15082.95622 7909.12523)))
("SF_SOLAR" 1 ((15107.46606 7867.64706) (15109.35147 7869.53247) (15111.23676 7867.64706) (15109.35147 7865.76165)))
("SF_SOLAR" 1 ((15115.00758 7882.72998) (15116.89287 7884.61538) (15118.77828 7882.72998) (15116.89287 7880.84468)))
("SF_SOLAR" 1 ((15141.40271 7973.22771) (15143.28812 7975.11312) (15145.17342 7973.22771) (15143.28812 7971.34242)))
("SF_SOLAR" 1 ((15152.71493 7992.08145) (15154.60034 7993.96686) (15156.48563 7992.08145) (15154.60034 7990.19604)))
("SF_SOLAR" 1 ((15154.60034 8071.26697) (15156.48563 8073.15238) (15158.37104 8071.26697) (15156.48563 8069.38156)))
("SF_SOLAR" 1 ((15156.48563 7978.88382) (15158.37104 7980.76923) (15160.25645 7978.88382) (15158.37104 7976.99853)))
("SF_SOLAR" 1 ((15169.68326 8084.46459) (15171.56867 8086.34989) (15173.45396 8084.46459) (15171.56867 8082.57919)))
("SF_PLANTING" 1 ((15180.99548 296.00305) (15182.88088 297.88835) (15184.76618 296.00305) (15182.88088 294.11765)))
("SF_SOLAR" 1 ((15186.65158 8041.10102) (15188.53699 8042.98643) (15190.42229 8041.10102) (15188.53699 8039.21572)))
("SF_SOLAR" 1 ((15211.16143 8084.46459) (15213.04672 8086.34989) (15214.93213 8084.46459) (15213.04672 8082.57919)))
("SF_SOLAR" 1 ((15216.81753 8075.03767) (15218.70283 8076.92308) (15220.58824 8075.03767) (15218.70283 8073.15238)))
("SF_SOLAR" 1 ((15220.58824 8097.66210) (15222.47364 8099.54751) (15224.35894 8097.66210) (15222.47364 8095.77681)))
("SF_SOLAR" 1 ((15224.35894 8178.73303) (15226.24434 8180.61844) (15228.12975 8178.73303) (15226.24434 8176.84762)))
("SF_SOLAR" 1 ((15239.44197 7926.09355) (15241.32726 7927.97885) (15243.21267 7926.09355) (15241.32726 7924.20814)))
("SF_SOLAR" 1 ((15258.29559 8144.79638) (15260.18100 8146.68179) (15262.06640 8144.79638) (15260.18100 8142.91097)))
("SF_SOLAR" 1 ((15258.29559 7867.64706) (15260.18100 7869.53247) (15262.06640 7867.64706) (15260.18100 7865.76165)))
("SF_SOLAR" 1 ((15263.95170 7886.50079) (15265.83710 7888.38609) (15267.72251 7886.50079) (15265.83710 7884.61538)))
("SF_SOLAR" 1 ((15265.83710 8190.04525) (15267.72251 8191.93066) (15269.60781 8190.04525) (15267.72251 8188.15984)))
("SF_SOLAR" 1 ((15273.37862 8195.70136) (15275.26391 8197.58676) (15277.14932 8195.70136) (15275.26391 8193.81595)))
("SF_SOLAR" 1 ((15273.37862 8082.57919) (15275.26391 8084.46459) (15277.14932 8082.57919) (15275.26391 8080.69378)))
("SF_SOLAR" 1 ((15279.03473 8171.19152) (15280.92002 8173.07692) (15282.80543 8171.19152) (15280.92002 8169.30622)))
("SF_SOLAR" 1 ((15288.46154 7843.13722) (15290.34695 7845.02262) (15292.23224 7843.13722) (15290.34695 7841.25192)))
("SF_SOLAR" 1 ((15303.54446 7948.71799) (15305.42986 7950.60328) (15307.31527 7948.71799) (15305.42986 7946.83258)))
("SF_SOLAR" 1 ((15303.54446 7843.13722) (15305.42986 7845.02262) (15307.31527 7843.13722) (15305.42986 7841.25192)))
("SF_SOLAR" 1 ((15307.31527 8195.70136) (15309.20057 8197.58676) (15311.08597 8195.70136) (15309.20057 8193.81595)))
("SF_SOLAR" 1 ((15311.08597 8152.33790) (15312.97138 8154.22319) (15314.85667 8152.33790) (15312.97138 8150.45249)))
("SF_SOLAR" 1 ((15329.93971 8178.73303) (15331.82500 8180.61844) (15333.71041 8178.73303) (15331.82500 8176.84762)))
("SF_SOLAR" 1 ((15329.93971 7867.64706) (15331.82500 7869.53247) (15333.71041 7867.64706) (15331.82500 7865.76165)))
("SF_SOLAR" 1 ((15333.71041 7886.50079) (15335.59581 7888.38609) (15337.48111 7886.50079) (15335.59581 7884.61538)))
("SF_SOLAR" 1 ((15341.25192 7843.13722) (15343.13722 7845.02262) (15345.02262 7843.13722) (15343.13722 7841.25192)))
("SF_SOLAR" 1 ((15352.56414 8152.33790) (15354.44943 8154.22319) (15356.33484 8152.33790) (15354.44943 8150.45249)))
("SF_SOLAR" 1 ((15352.56414 7980.76923) (15354.44943 7982.65464) (15356.33484 7980.76923) (15354.44943 7978.88382)))
("SF_SOLAR" 1 ((15375.18857 8152.33790) (15377.07387 8154.22319) (15378.95928 8152.33790) (15377.07387 8150.45249)))
("SF_PLANTING" 1 ((15388.38609 3897.05882) (15390.27149 3898.94423) (15392.15690 3897.05882) (15390.27149 3895.17342)))
("SF_SOLAR" 1 ((15397.81301 8129.71346) (15399.69830 8131.59876) (15401.58371 8129.71346) (15399.69830 8127.82805)))
("SF_SOLAR" 1 ((15399.69830 7871.41776) (15401.58371 7873.30317) (15403.46912 7871.41776) (15401.58371 7869.53247)))
("SF_SOLAR" 1 ((15412.89593 7965.68631) (15414.78133 7967.57161) (15416.66663 7965.68631) (15414.78133 7963.80090)))
("SF_SOLAR" 1 ((15418.55204 8131.59876) (15420.43744 8133.48416) (15422.32274 8131.59876) (15420.43744 8129.71346)))
("SF_SOLAR" 1 ((15424.20814 8152.33790) (15426.09355 8154.22319) (15427.97885 8152.33790) (15426.09355 8150.45249)))
("SF_SOLAR" 1 ((15424.20814 7963.80090) (15426.09355 7965.68631) (15427.97885 7963.80090) (15426.09355 7961.91550)))
("SF_SOLAR" 1 ((15480.76923 8016.59129) (15482.65464 8018.47658) (15484.53993 8016.59129) (15482.65464 8014.70588)))
("SF_SOLAR" 1 ((15488.31075 7918.55204) (15490.19604 7920.43744) (15492.08145 7918.55204) (15490.19604 7916.66663)))
("SF_SOLAR" 1 ((15510.93518 7978.88382) (15512.82048 7980.76923) (15514.70588 7978.88382) (15512.82048 7976.99853)))
("SF_SOLAR" 1 ((15510.93518 7963.80090) (15512.82048 7965.68631) (15514.70588 7963.80090) (15512.82048 7961.91550)))
("SF_SOLAR" 1 ((15510.93518 7890.27149) (15512.82048 7892.15690) (15514.70588 7890.27149) (15512.82048 7888.38609)))
("SF_SOLAR" 1 ((15510.93518 7871.41776) (15512.82048 7873.30317) (15514.70588 7871.41776) (15512.82048 7869.53247)))
("SF_PLANTING" 1 ((15524.13269 3661.38767) (15526.01810 3663.27296) (15527.90351 3661.38767) (15526.01810 3659.50226)))
("SF_SOLAR" 1 ((15529.78880 7867.64706) (15531.67421 7869.53247) (15533.55962 7867.64706) (15531.67421 7865.76165)))
("SF_SOLAR" 1 ((15541.10102 8144.79638) (15542.98643 8146.68179) (15544.87183 8144.79638) (15542.98643 8142.91097)))
("SF_SOLAR" 1 ((15541.10102 8110.85973) (15542.98643 8112.74514) (15544.87183 8110.85973) (15542.98643 8108.97432)))
("SF_SOLAR" 1 ((15544.87183 8180.61844) (15546.75713 8182.50373) (15548.64253 8180.61844) (15546.75713 8178.73303)))
("SF_MASONRY_AND_ARCH" 1 ((15559.95475 2296.38009) (15561.84016 2298.26550) (15563.72545 2296.38009) (15561.84016
2294.49468)))
("SF_SOLAR" 1 ((15593.89140 8152.33790) (15595.77681 8154.22319) (15597.66210 8152.33790) (15595.77681 8150.45249)))
("SF_SOLAR" 1 ((15601.43292 8180.61844) (15603.31821 8182.50373) (15605.20362 8180.61844) (15603.31821 8178.73303)))
("SF_SOLAR" 1 ((15601.43292 8131.59876) (15603.31821 8133.48416) (15605.20362 8131.59876) (15603.31821 8129.71346)))
("SF_SOLAR" 1 ((15624.05735 8152.33790) (15625.94265 8154.22319) (15627.82805 8152.33790) (15625.94265 8150.45249)))
("SF_SOLAR" 1 ((15642.91097 7990.19604) (15644.79638 7992.08145) (15646.68179 7990.19604) (15644.79638 7988.31075)))
("SF_SOLAR" 1 ((15646.68179 8152.33790) (15648.56708 8154.22319) (15650.45249 8152.33790) (15648.56708 8150.45249)))
("SF_SOLAR" 1 ((15646.68179 7931.74966) (15648.56708 7933.63495) (15650.45249 7931.74966) (15648.56708 7929.86425)))
("SF_SOLAR" 1 ((15646.68179 7892.15690) (15648.56708 7894.04219) (15650.45249 7892.15690) (15648.56708 7890.27149)))
("SF_SOLAR" 1 ((15650.45249 8024.13269) (15652.33790 8026.01810) (15654.22319 8024.13269) (15652.33790 8022.24740)))
("SF_SOLAR" 1 ((15661.76471 7873.30317) (15663.65011 7875.18857) (15665.53541 7873.30317) (15663.65011 7871.41776)))
("SF_SOLAR" 1 ((15669.30622 8152.33790) (15671.19152 8154.22319) (15673.07692 8152.33790) (15671.19152 8150.45249)))
("SF_SOLAR" 1 ((15669.30622 8050.52794) (15671.19152 8052.41324) (15673.07692 8050.52794) (15671.19152 8048.64253)))
("SF_SOLAR" 1 ((15673.07692 7897.81301) (15674.96233 7899.69830) (15676.84762 7897.81301) (15674.96233 7895.92760)))
("SF_SOLAR" 1 ((15673.07692 7854.44943) (15674.96233 7856.33484) (15676.84762 7854.44943) (15674.96233 7852.56414)))
("SF_SOLAR" 1 ((15676.84762 7956.25939) (15678.73303 7958.14480) (15680.61844 7956.25939) (15678.73303 7954.37410)))
("SF_SOLAR" 1 ((15684.38914 7918.55204) (15686.27455 7920.43744) (15688.15984 7918.55204) (15686.27455 7916.66663)))
("SF_SOLAR" 1 ((15691.93066 8152.33790) (15693.81595 8154.22319) (15695.70136 8152.33790) (15693.81595 8150.45249)))
("SF_SOLAR" 1 ((15691.93066 8133.48416) (15693.81595 8135.36957) (15695.70136 8133.48416) (15693.81595 8131.59876)))
("SF_SOLAR" 1 ((15695.70136 7937.40577) (15697.58676 7939.29106) (15699.47206 7937.40577) (15697.58676 7935.52036)))
("SF_SOLAR" 1 ((15707.01357 7952.48869) (15708.89898 7954.37410) (15710.78428 7952.48869) (15708.89898 7950.60328)))
("SF_SOLAR" 1 ((15710.78428 8009.04977) (15712.66968 8010.93518) (15714.55509 8009.04977) (15712.66968 8007.16437)))
("SF_SOLAR" 1 ((15729.63801 7988.31075) (15731.52342 7990.19604) (15733.40871 7988.31075) (15731.52342 7986.42534)))
("SF_SOLAR" 1 ((15733.40871 8044.87183) (15735.29412 8046.75713) (15737.17952 8044.87183) (15735.29412 8042.98643)))
("SF_SOLAR" 1 ((15737.17952 8148.56708) (15739.06482 8150.45249) (15740.95023 8148.56708) (15739.06482 8146.68179)))
("SF_SOLAR" 1 ((15740.95023 8005.27907) (15742.83563 8007.16437) (15744.72093 8005.27907) (15742.83563 8003.39367)))
("SF_SOLAR" 1 ((15742.83563 8058.06934) (15744.72093 8059.95475) (15746.60633 8058.06934) (15744.72093 8056.18405)))
("SF_SOLAR" 1 ((15752.26244 8095.77681) (15754.14785 8097.66210) (15756.03314 8095.77681) (15754.14785 8093.89140)))
("SF_SOLAR" 1 ((15754.14785 8076.92308) (15756.03314 8078.80848) (15757.91855 8076.92308) (15756.03314 8075.03767)))
("SF_SOLAR" 1 ((15754.14785 8022.24740) (15756.03314 8024.13269) (15757.91855 8022.24740) (15756.03314 8020.36199)))
("SF_MASONRY_AND_ARCH" 1 ((15754.14785 2599.92455) (15756.03314 2601.80995) (15757.91855 2599.92455) (15756.03314
2598.03925)))
("SF_SOLAR" 1 ((15759.80396 8176.84762) (15761.68925 8178.73303) (15763.57466 8176.84762) (15761.68925 8174.96233)))
("SF_SOLAR" 1 ((15765.46007 8095.77681) (15767.34536 8097.66210) (15769.23077 8095.77681) (15767.34536 8093.89140)))
("SF_SOLAR" 1 ((15765.46007 8041.10102) (15767.34536 8042.98643) (15769.23077 8041.10102) (15767.34536 8039.21572)))
("SF_SOLAR" 1 ((15774.88688 8061.84016) (15776.77229 8063.72545) (15778.65758 8061.84016) (15776.77229 8059.95475)))
("SF_SOLAR" 1 ((15776.77229 8114.63043) (15778.65758 8116.51584) (15780.54299 8114.63043) (15778.65758 8112.74514)))
("SF_SOLAR" 1 ((15786.19910 8076.92308) (15788.08450 8078.80848) (15789.96980 8076.92308) (15788.08450 8075.03767)))
("SF_SOLAR" 1 ((15797.51131 8095.77681) (15799.39672 8097.66210) (15801.28201 8095.77681) (15799.39672 8093.89140)))
("SF_SOLAR" 1 ((15801.28201 8190.04525) (15803.16742 8191.93066) (15805.05283 8190.04525) (15803.16742 8188.15984)))
("SF_SOLAR" 1 ((15808.82353 8112.74514) (15810.70894 8114.63043) (15812.59423 8112.74514) (15810.70894 8110.85973)))
("SF_SOLAR" 1 ((15812.59423 8165.53541) (15814.47964 8167.42081) (15816.36505 8165.53541) (15814.47964 8163.65011)))
("SF_PLANTING" 1 ((15818.25034 1210.40724) (15820.13575 1212.29265) (15822.02115 1210.40724) (15820.13575 1208.52183)))
("SF_SOLAR" 1 ((15820.13575 8129.71346) (15822.02115 8131.59876) (15823.90645 8129.71346) (15822.02115 8127.82805)))
("SF_MASONRY_AND_ARCH" 1 ((15822.02115 1385.74661) (15823.90645 1387.63201) (15825.79186 1385.74661) (15823.90645
1383.86120)))
("SF_SOLAR" 1 ((15831.44796 8146.68179) (15833.33337 8148.56708) (15835.21867 8146.68179) (15833.33337 8144.79638)))
("SF_PLANTING" 1 ((15840.87477 603.31821) (15842.76018 605.20362) (15844.64559 603.31821) (15842.76018 601.43292)))
("SF_SOLAR" 1 ((15846.53088 8163.65011) (15848.41629 8165.53541) (15850.30170 8163.65011) (15848.41629 8161.76471)))
("SF_SOLAR" 1 ((15848.41629 8212.66968) (15850.30170 8214.55509) (15852.18699 8212.66968) (15850.30170 8210.78428)))
("SF_SOLAR" 1 ((15857.84310 8180.61844) (15859.72851 8182.50373) (15861.61391 8180.61844) (15859.72851 8178.73303)))
("SF_SOLAR" 1 ((15869.15532 8203.24287) (15871.04072 8205.12817) (15872.92613 8203.24287) (15871.04072 8201.35747)))
("SF_MASONRY_AND_ARCH" 1 ((15871.04072 1021.87025) (15872.92613 1023.75566) (15874.81143 1021.87025) (15872.92613
1019.98495)))
("SF_MASONRY_AND_ARCH" 1 ((15895.55057 2102.18699) (15897.43586 2104.07240) (15899.32127 2102.18699) (15897.43586
2100.30170)))
("SF_MASONRY_AND_ARCH" 1 ((15929.48722 2428.35600) (15931.37251 2430.24129) (15933.25792 2428.35600) (15931.37251
2426.47059)))
("SF_MASONRY_AND_ARCH" 1 ((15984.16290 2454.75113) (15986.04830 2456.63654) (15987.93360 2454.75113) (15986.04830
2452.86572)))
("SF_MASONRY_AND_ARCH" 1 ((16010.55803 1745.85215) (16012.44344 1747.73756) (16014.32885 1745.85215) (16012.44344
1743.96686)))
("SF_MASONRY_AND_ARCH" 1 ((16069.00452 2788.46154) (16070.88993 2790.34695) (16072.77523 2788.46154) (16070.88993
2786.57613)))
("SF_MASONRY_AND_ARCH" 1 ((16101.05577 3503.01663) (16102.94118 3504.90192) (16104.82658 3503.01663) (16102.94118
3501.13122)))
("SF_MASONRY_AND_ARCH" 1 ((16155.73156 2937.40577) (16157.61686 2939.29106) (16159.50226 2937.40577) (16157.61686
2935.52036)))
("SF_MASONRY_AND_ARCH" 1 ((16161.38767 3010.93518) (16163.27296 3012.82048) (16165.15837 3010.93518) (16163.27296
3009.04977)))
("SF_MASONRY_AND_ARCH" 1 ((16165.15837 3265.46007) (16167.04378 3267.34536) (16168.92907 3265.46007) (16167.04378
3263.57466)))
("SF_ARCHITECTURE" 1 ((16219.83405 5761.68925) (16221.71946 5763.57466) (16223.60486 5761.68925) (16221.71946
5759.80396)))
("SF_MASONRY_AND_ARCH" 1 ((16300.90498 2965.68631) (16302.79038 2967.57161) (16304.67568 2965.68631) (16302.79038
2963.80090)))
("SF_MASONRY_AND_ARCH" 1 ((16334.84163 3295.62590) (16336.72704 3297.51131) (16338.61233 3295.62590) (16336.72704
3293.74061)))
("SF_MASONRY_AND_ARCH" 1 ((16410.25645 3184.38914) (16412.14174 3186.27455) (16414.02715 3184.38914) (16412.14174
3182.50373)))
("SF_MASONRY_AND_ARCH" 1 ((16444.19310 969.07998) (16446.07839 970.96527) (16447.96380 969.07998) (16446.07839
967.19457)))
("SF_MASONRY_AND_ARCH" 1 ((16455.50532 2373.68020) (16457.39061 2375.56561) (16459.27602 2373.68020) (16457.39061
2371.79491)))
("SF_MASONRY_AND_ARCH" 1 ((16536.57613 3438.91403) (16538.46154 3440.79943) (16540.34695 3438.91403) (16538.46154
3437.02862)))
("SF_MASONRY_AND_ARCH" 1 ((16662.89593 2554.67568) (16664.78133 2556.56109) (16666.66663 2554.67568) (16664.78133
2552.79038)))
("SF_MASONRY_AND_ARCH" 1 ((16664.78133 2368.02410) (16666.66663 2369.90950) (16668.55204 2368.02410) (16666.66663
2366.13880)))
("SF_PLANTING" 1 ((16676.09355 761.68925) (16677.97885 763.57466) (16679.86425 761.68925) (16677.97885 759.80396)))
("SF_MASONRY_AND_ARCH" 1 ((16687.40577 3423.83111) (16689.29106 3425.71640) (16691.17647 3423.83111) (16689.29106
3421.94570)))
("SF_PLANTING" 1 ((16743.96686 6523.37862) (16745.85215 6525.26391) (16747.73756 6523.37862) (16745.85215 6521.49321)))
("SF_MASONRY_AND_ARCH" 1 ((16755.27907 1691.17647) (16757.16437 1693.06188) (16759.04977 1691.17647) (16757.16437
1689.29106)))
("SF_MASONRY_AND_ARCH" 1 ((16787.33032 1455.50532) (16789.21572 1457.39061) (16791.10102 1455.50532) (16789.21572
1453.61991)))
("SF_MASONRY_AND_ARCH" 1 ((16815.61086 2043.74061) (16817.49627 2045.62590) (16819.38156 2043.74061) (16817.49627
2041.85520)))
("SF_MASONRY_AND_ARCH" 1 ((16832.57919 3103.31821) (16834.46459 3105.20362) (16836.34989 3103.31821) (16834.46459
3101.43292)))
("SF_PLANTING" 1 ((16929.41380 6626.24480) (16930.46324 6640.27127) (16926.69344 6647.51007) (16911.77161 6646.61516)
(16905.42783 6640.26493) (16904.37839 6625.19536) (16908.14819 6618.85792)))
("SF_MASONRY_AND_ARCH" 1 ((16983.40871 2846.90803) (16985.29412 2848.79333) (16987.17952 2846.90803) (16985.29412
2845.02262)))
("SF_MASONRY_AND_ARCH" 1 ((16987.17952 2812.97138) (16989.06482 2814.85667) (16990.95023 2812.97138) (16989.06482
2811.08597)))
("SF_PLANTING" 1 ((17004.14785 7045.62590) (17006.03314 7047.51131) (17007.91855 7045.62590) (17006.03314 7043.74061)))
("SF_MASONRY_AND_ARCH" 1 ((17072.02115 1151.96075) (17073.90645 1153.84615) (17075.79186 1151.96075) (17073.90645
1150.07545)))
("SF_PLANTING" 1 ((17173.83111 411.01052) (17175.71640 412.89593) (17177.60181 411.01052) (17175.71640 409.12523)))
("SF_MASONRY_AND_ARCH" 1 ((17175.71640 2409.50226) (17177.60181 2411.38767) (17179.48722 2409.50226) (17177.60181
2407.61686)))
("SF_MASONRY_AND_ARCH" 1 ((17177.60181 3097.66210) (17179.48722 3099.54751) (17181.37251 3097.66210) (17179.48722
3095.77681)))
("SF_MASONRY_AND_ARCH" 1 ((17181.37251 1661.01052) (17183.25792 1662.89593) (17185.14333 1661.01052) (17183.25792
1659.12523)))
("SF_PLANTING" 1 ((17664.02715 3723.60486) (17665.91256 3725.49016) (17667.79785 3723.60486) (17665.91256 3721.71946)))
("SF_PLANTING" 1 ((17669.68326 3559.57771) (17671.56867 3561.46301) (17673.45396 3559.57771) (17671.56867 3557.69231)))
("SF_PLANTING" 1 ((17714.93213 3482.27749) (17716.81753 3484.16290) (17718.70283 3482.27749) (17716.81753 3480.39219)))
("SF_ARCHITECTURE" 1 ((17848.79333 5018.85373) (17850.67873 5020.73903) (17852.56414 5018.85373) (17850.67873
5016.96833)))
("SF_PLANTING" 1 ((18508.67274 3804.67568) (18510.55803 3806.56109) (18512.44344 3804.67568) (18510.55803 3802.79038)))
("SF_PLANTING" 1 ((18569.00452 3687.78281) (18570.88993 3689.66821) (18572.77523 3687.78281) (18570.88993 3685.89740)))
("SF_PLANTING" 1 ((18587.85826 3691.55351) (18589.74355 3693.43891) (18591.62896 3691.55351) (18589.74355 3689.66821)))
("SF_PLANTING" 1 ((18597.28507 3503.01663) (18599.17048 3504.90192) (18601.05577 3503.01663) (18599.17048 3501.13122)))
("SF_ARCHITECTURE" 1 ((18642.53394 4458.89898) (18644.41934 4460.78428) (18646.30464 4458.89898) (18644.41934
4457.01357)))
("SF_PLANTING" 1 ((18808.44649 3214.55509) (18810.33179 3216.44038) (18812.21719 3214.55509) (18810.33179 3212.66968)))
("SF_PLANTING" 1 ((19057.62410 1138.76414) (19068.62557 1152.78982) (19098.79525 1161.24016) (19117.64706 1156.56029)
(19130.46991 1142.53394) (19125.04027 1131.37636) (19117.64706 1127.60520) (19068.62557 1127.60520) (19061.23925
1131.37636)))
("SF_PLANTING" 1 ((19110.26075 3294.56934) (19121.41968 3298.19208) (19132.57579 3291.70679) (19136.19785 3284.31346)
(19128.81154 3270.43495) (19117.65396 3270.43495) (19111.16244 3276.77873) (19106.63722 3288.07783)))
("SF_PLANTING" 1 ((19198.71799 3661.38767) (19200.60328 3663.27296) (19202.48869 3661.38767) (19200.60328 3659.50226)))
("SF_PLANTING" 1 ((19200.60328 3470.96527) (19202.48869 3472.85068) (19204.37410 3470.96527) (19202.48869 3469.07998)))
("SF_PLANTING" 1 ((19200.60328 614.63043) (19202.48869 616.51584) (19204.37410 614.63043) (19202.48869 612.74514)))
("SF_PLANTING" 1 ((19205.57771 3558.37376) (19219.45701 3558.52149) (19238.15554 3544.49446) (19243.74683 3529.41176)
(19238.16244 3518.26109) (19230.76923 3515.54005) (19215.83495 3525.64751) (19205.42998 3544.49446)))
))
(setq SF:LAYERS '("SF_ARCHITECTURE" "SF_MASONRY_AND_ARCH" "SF_PLANTING" "SF_SOLAR"))
(setq SF:BLOCK "SF_REFERENCE_CD4BB8B69C")

(defun SF:POLY (row / pts)
  (setq pts (caddr row))
  (entmake
    (append
      (list '(0 . "LWPOLYLINE") '(100 . "AcDbEntity")
            (cons 8 (car row)) '(6 . "Continuous") '(62 . 7)
            '(420 . 0) '(370 . 13) '(100 . "AcDbPolyline")
            (cons 90 (length pts)) (cons 70 (cadr row)) '(43 . 0.0))
      (mapcar '(lambda (pt) (cons 10 pt)) pts))))
(defun SF:BUILD (name / row)
  (entmake (list '(0 . "BLOCK") '(100 . "AcDbEntity") '(8 . "0")
    '(100 . "AcDbBlockBegin") (cons 2 name) '(70 . 0)
    '(10 0.0 0.0 0.0) (cons 3 name) '(1 . "")))
  (foreach row SF:DATA (SF:POLY row))
  (entmake '((0 . "ENDBLK") (100 . "AcDbEntity") (8 . "0")
    (100 . "AcDbBlockEnd"))))
(defun c:SUSTAIN (/ pt width fac name)
  (setq pt (getpoint "\nChoose insertion point: "))
  (if pt
    (progn
      (initget 6)
      (setq width (getreal "\nEstimated baseline width in mm <20000>: "))
      (if (null width) (setq width 20000.0))
      (setq fac (/ width 20000.0))
      (foreach name SF:LAYERS
        (if (null (tblsearch "LAYER" name))
          (entmake (list '(0 . "LAYER") '(100 . "AcDbSymbolTableRecord")
            '(100 . "AcDbLayerTableRecord") (cons 2 name) '(70 . 0)
            '(62 . 7) '(420 . 0) '(6 . "Continuous") '(370 . 13)))))
      (if (null (tblsearch "BLOCK" SF:BLOCK)) (SF:BUILD SF:BLOCK))
      (entmake (list '(0 . "INSERT") '(100 . "AcDbEntity") '(8 . "0")
        '(100 . "AcDbBlockReference") (cons 2 SF:BLOCK)
        (cons 10 (trans pt 1 0)) (cons 41 fac) (cons 42 fac)
        (cons 43 fac) '(50 . 0.0)))
      (princ "\nInserted source-traced facade. EXPLODE for individual editable paths.")
      (princ "\nBlack linework: use a white model-space background. Dimensions are estimated.")))
  (princ))
(princ "\nLoaded sustainable facade. Run SUSTAIN.")
(princ)
